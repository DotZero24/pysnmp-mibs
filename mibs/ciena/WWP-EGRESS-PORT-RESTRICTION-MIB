--
 -- WWP-EGRESS-PORT-RESTRICTION-MIB.my
 --


 WWP-EGRESS-PORT-RESTRICTION-MIB DEFINITIONS ::= BEGIN

 IMPORTS
	TEXTUAL-CONVENTION FROM SNMPv2-TC
   Integer32, OBJECT-TYPE, MODULE-IDENTITY
	    FROM SNMPv2-SMI
   RowStatus
            FROM SNMPv2-TC
   wwpModules
	    FROM WWP-SMI;

 wwpEgressPortRestrictionMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP EGRESS-PORT-RESTRICTION cobjects."
	    REVISION    "200104031700Z"
	    DESCRIPTION
		    "Initial creation."
	    ::= { wwpModules 34 }


 --
 -- Textual conventions
 --

 PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING (SIZE (0..255))


 VlanId ::= TEXTUAL-CONVENTION
    STATUS      current
    DESCRIPTION
        "A 12-bit VLAN ID used in the VLAN Tag header."
    SYNTAX      INTEGER (1..4094)


 --
 -- Node definitions
 --

 wwpEgressPortRestrictionMIBObjects OBJECT IDENTIFIER ::= { wwpEgressPortRestrictionMIB 1 }

 wwpEgressPortRestriction OBJECT IDENTIFIER ::= { wwpEgressPortRestrictionMIBObjects 1 }


 -- Notifications

 wwpEgressPortRestrictionNotificationPrefix     OBJECT IDENTIFIER ::= { wwpEgressPortRestrictionMIB 2 }
 wwpEgressPortRestrictionNotifications          OBJECT IDENTIFIER ::=
                       { wwpEgressPortRestrictionNotificationPrefix 0 }

 -- Conformance information

 wwpEgressPortRestrictionMIBConformance OBJECT IDENTIFIER ::= { wwpEgressPortRestrictionMIB 3 }
 wwpEgressPortRestrictionMIBCompliances OBJECT IDENTIFIER ::= { wwpEgressPortRestrictionMIBConformance 1 }
 wwpEgressPortRestrictionMIBGroups      OBJECT IDENTIFIER ::= { wwpEgressPortRestrictionMIBConformance 2 }

 wwpEgressPortRestrictionTable OBJECT-TYPE
     SYNTAX       SEQUENCE OF WwpEgressPortRestrictionEntry
     MAX-ACCESS   not-accessible
     STATUS       current
     DESCRIPTION
	     "A Table of EgressPortRestriction Entries."
     ::= { wwpEgressPortRestriction 1 }

 wwpEgressPortRestrictionEntry  OBJECT-TYPE
     SYNTAX       WwpEgressPortRestrictionEntry
     MAX-ACCESS   not-accessible
     STATUS       current
     DESCRIPTION
	     "The EgressPortRestriction per vlan per source port Entry in the Table."
     INDEX { wwpERestVlanId, wwpERestPortId }
     ::= { wwpEgressPortRestrictionTable 1 }

 WwpEgressPortRestrictionEntry ::= SEQUENCE {
     wwpERestVlanId           VlanId,
     wwpERestPortId           INTEGER,
     wwpERestEgreesPorts      PortList,
     wwpERestStatus           RowStatus
  }


 wwpERestVlanId     OBJECT-TYPE
     SYNTAX         VlanId
     MAX-ACCESS     read-only
     STATUS         current
     DESCRIPTION
	     "Vlan ID for this instance of EgressPortRestrictionEntry.
             This Vlan Id should refer to the  wwpVlanId in the WwpVlanEntry."
     ::= { wwpEgressPortRestrictionEntry 1 }

 wwpERestPortId     OBJECT-TYPE
     SYNTAX         INTEGER (1..65535)
     MAX-ACCESS     read-only
     STATUS         current
     DESCRIPTION
	     "The source port Id for this instance of EgressPortRestrictionEntry.
             Port ID's start at 1, and are consecutive for each
             additional port. This port Id should refer to the dot1dBasePort
             in the Dot1dBasePortEntry."
     ::= { wwpEgressPortRestrictionEntry 2 }

 wwpERestEgreesPorts  OBJECT-TYPE
     SYNTAX           PortList
     MAX-ACCESS       read-write
     STATUS           current
     DESCRIPTION
             "The allowed egress ports on which Egress Port Restriction
             (EPR) allows for the configuration, on a per-port/per-Vlan basis."
     DEFVAL { '0000'h }
     ::= { wwpEgressPortRestrictionEntry 3 }


 wwpERestStatus     OBJECT-TYPE
     SYNTAX         RowStatus
     MAX-ACCESS     read-create
     STATUS         current
     DESCRIPTION
	     "Used to manage the creation and deletion of the
	     conceptual rows in this table.

             To create a row in this table, a manager must
             set this object to 'createAndGo'."
     ::= { wwpEgressPortRestrictionEntry 4 }


 END

 --
 -- WWP-EGRESS-PORT-RESTRICTION-MIB
 --
