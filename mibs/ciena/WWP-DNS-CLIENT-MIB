--
 -- WWP-DNS-CLIENT-MIB.my
 --

 WWP-DNS-CLIENT-MIB DEFINITIONS ::= BEGIN

 IMPORTS
    IpAddress, Integer32, OBJECT-TYPE, MODULE-IDENTITY
	FROM SNMPv2-SMI
    DisplayString, RowStatus, TruthValue
	FROM SNMPv2-TC
    wwpModules
	FROM WWP-SMI;

 wwpDnsClientMIB MODULE-IDENTITY
    LAST-UPDATED "200303191012Z"
    ORGANIZATION
	     "   World Wide Packets Inc"
    CONTACT-INFO
	     "   Mib Meister
	         Postal: World Wide Packets
		 P.O. Box 950
		 Veradale, WA 99037
		 USA
		 Phone:  +1 509 242 9000
		 Email:  mib.meister@worldwidepackets.com"

     DESCRIPTION
	     "A MIB module to manage dns client on the
	     WWP products."
     REVISION    "200303191012Z"
     DESCRIPTION
	     "Initial Creation"
     ::= { wwpModules 49 }


 --
 -- Node definitions
 --

 wwpDnsClientMIBObjects OBJECT IDENTIFIER ::= { wwpDnsClientMIB 1 }

 wwpDnsClient  OBJECT IDENTIFIER ::= { wwpDnsClientMIBObjects 1 }

 -- Notifications

 wwpDnsClientMIBNotificationPrefix  OBJECT IDENTIFIER ::= { wwpDnsClientMIB 2 }
 wwpDnsClientMIBNotifications       OBJECT IDENTIFIER ::=
                       { wwpDnsClientMIBNotificationPrefix 0 }

 -- Conformance information

 wwpDnsClientMIBConformance OBJECT IDENTIFIER ::= { wwpDnsClientMIB 3 }
 wwpDnsClientMIBCompliances OBJECT IDENTIFIER ::= { wwpDnsClientMIBConformance 1 }
 wwpDnsClientMIBGroups      OBJECT IDENTIFIER ::= { wwpDnsClientMIBConformance 2 }

 -- The system wide parameters

 wwpDnsResolverEnable OBJECT-TYPE
     SYNTAX      TruthValue
     MAX-ACCESS  read-write
     STATUS      current
     DESCRIPTION
             "Specifies whether or not the DNS Resolver is enabled."
     DEFVAL { true }
     ::= { wwpDnsClient 1 }

 wwpDnsDomainAdminName OBJECT-TYPE
     SYNTAX      DisplayString (SIZE(1..128))
     MAX-ACCESS  read-write
     STATUS      current
     DESCRIPTION
             "The configured DNS Domain Name."
     ::= { wwpDnsClient 2 }

 wwpDnsDomainOperName OBJECT-TYPE
     SYNTAX      DisplayString (SIZE(1..128))
     MAX-ACCESS  read-only
     STATUS      current
     DESCRIPTION
             "The operational DNS Domain Name.
	      DNS Domain name can be obtained by DHCP,
	      so the operational DNS Domain Name can be
	      different from Admin DNS Domain Name."
     ::= { wwpDnsClient 3 }

 -- -------------------------------------------------------------
 -- The DNS Name Admin Server Table
 -- -------------------------------------------------------------
 -- Each row in this table defines a dns name server
 --

 wwpDnsNameAdminServerTable OBJECT-TYPE
     SYNTAX      SEQUENCE OF WwpDnsNameAdminServerEntry
     MAX-ACCESS  not-accessible
     STATUS      current
     DESCRIPTION
             "A table containing configured DNS Servers information."
     ::= { wwpDnsClient 4 }

 wwpDnsNameAdminServerEntry OBJECT-TYPE
     SYNTAX      WwpDnsNameAdminServerEntry
     MAX-ACCESS  not-accessible
     STATUS      current
     DESCRIPTION
             "Defines the information pertaining to a configured DNS
	      Server."
     INDEX  { wwpDnsAdminServerId }
     ::= { wwpDnsNameAdminServerTable 1 }


 WwpDnsNameAdminServerEntry ::=
     SEQUENCE {
         wwpDnsAdminServerId
              Integer32,
	 wwpDnsAdminServerAddr
	      IpAddress,
         wwpDnsAdminServerStatus
              RowStatus
     }

 wwpDnsAdminServerId OBJECT-TYPE
     SYNTAX      Integer32(1..2147483647)
     MAX-ACCESS  read-only
     STATUS      current
     DESCRIPTION
             "A unique identifier for the configured DNS Server."
     ::= { wwpDnsNameAdminServerEntry 1 }

 wwpDnsAdminServerAddr OBJECT-TYPE
     SYNTAX      IpAddress
     MAX-ACCESS  read-create
     STATUS      current
     DESCRIPTION
             "The Ip address for the configured DNS Server."
     ::= { wwpDnsNameAdminServerEntry 2 }

 wwpDnsAdminServerStatus OBJECT-TYPE
     SYNTAX      RowStatus
     MAX-ACCESS  read-create
     STATUS      current
     DESCRIPTION
             "This object is used to create and delete rows in the
	      wwpDnsServerTable. To create a new row the
	      management station must set the object to
	      'CreateAndGo'."
     ::= { wwpDnsNameAdminServerEntry 3 }

 -- -------------------------------------------------------------
 -- The DNS Name Operational Server Table
 -- -------------------------------------------------------------
 -- Each row in this table defines a dns name server
 --

 wwpDnsNameOperServerTable OBJECT-TYPE
     SYNTAX      SEQUENCE OF WwpDnsNameOperServerEntry
     MAX-ACCESS  not-accessible
     STATUS      current
     DESCRIPTION
             "A table containing operational DNS Servers information.
	     DNS server list can also be obtained by DHCP, so the
	     operational list of servers may not be same as admin
	     list of servers."
     ::= { wwpDnsClient 5 }

 wwpDnsNameOperServerEntry OBJECT-TYPE
     SYNTAX      WwpDnsNameOperServerEntry
     MAX-ACCESS  not-accessible
     STATUS      current
     DESCRIPTION
             "Defines the information pertaining to a operational DNS
	      Server."
     INDEX  { wwpDnsOperServerId }
     ::= { wwpDnsNameOperServerTable 1 }


 WwpDnsNameOperServerEntry ::=
     SEQUENCE {
         wwpDnsOperServerId
              Integer32,
	 wwpDnsOperServerAddr
	      IpAddress
     }

 wwpDnsOperServerId OBJECT-TYPE
     SYNTAX      Integer32(1..2147483647)
     MAX-ACCESS  read-only
     STATUS      current
     DESCRIPTION
             "A unique identifier for the operational DNS Server."
     ::= { wwpDnsNameOperServerEntry 1 }

 wwpDnsOperServerAddr OBJECT-TYPE
     SYNTAX      IpAddress
     MAX-ACCESS  read-only
     STATUS      current
     DESCRIPTION
             "The Ip address for the operational DNS Server."
     ::= { wwpDnsNameOperServerEntry 2 }


 END

 --
 -- WWP-DNS-CLIENT-MIB.my
 --
