--
 -- WWP-RADIUS-CLIENT-MIB.my
 --
 --

 WWP-RADIUS-CLIENT-MIB DEFINITIONS ::= BEGIN

 IMPORTS
   Gauge32, Counter32, TimeTicks, IpAddress, Integer32, OBJECT-TYPE, MODULE-IDENTITY
	    FROM SNMPv2-SMI
   DisplayString, RowStatus
	    FROM SNMPv2-TC
   wwpModules
	    FROM WWP-SMI;


 wwpRadiusClientMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP Radius Server specific configuration
                    and monitoring information."
	    REVISION    "200104031700Z"
	    DESCRIPTION
		    "Initial creation."
	    ::= { wwpModules 11 }

 --
 -- Node definitions
 --

 wwpRadiusClientMIBObjects OBJECT IDENTIFIER ::= { wwpRadiusClientMIB 1 }

 wwpRadiusClient OBJECT IDENTIFIER ::= {wwpRadiusClientMIBObjects 1 }

 -- Notifications

 wwpRadiusClientMIBNotificationPrefix  OBJECT IDENTIFIER ::= { wwpRadiusClientMIB 2 }
 wwpRadiusClientMIBNotifications       OBJECT IDENTIFIER ::=
                       { wwpRadiusClientMIBNotificationPrefix 0 }

 -- Conformance information

 wwpRadiusClientMIBConformance OBJECT IDENTIFIER ::= { wwpRadiusClientMIB 3 }
 wwpRadiusClientMIBCompliances OBJECT IDENTIFIER ::= { wwpRadiusClientMIBConformance 1 }
 wwpRadiusClientMIBGroups      OBJECT IDENTIFIER ::= { wwpRadiusClientMIBConformance 2 }


 wwpRadiusClientTimeout OBJECT-TYPE
     SYNTAX       Integer32 (1..3)
     UNITS        "seconds"
     MAX-ACCESS   read-write
     STATUS       current
     DESCRIPTION
	     "This is the time in seconds between retransmissions
	      to the RADIUS server."
     DEFVAL { 1 }
     ::= { wwpRadiusClient 1 }

 wwpRadiusClientRetries   OBJECT-TYPE
     SYNTAX         Integer32 (0..3)
     MAX-ACCESS     read-write
     STATUS         current
     DESCRIPTION
	     "Indicates the number of times the RADIUS server should be
	     tried before giving up on the server."
     DEFVAL { 3 }
     ::= { wwpRadiusClient 2 }

 wwpRadiusServerTable OBJECT-TYPE
     SYNTAX         SEQUENCE OF WwpRadiusServerEntry
     MAX-ACCESS     not-accessible
     STATUS         current
     DESCRIPTION
	     "Lists the possible RADIUS servers."
     ::= { wwpRadiusClient 3 }

 wwpRadiusServerEntry OBJECT-TYPE
     SYNTAX       WwpRadiusServerEntry
     MAX-ACCESS   not-accessible
     STATUS       current
     DESCRIPTION
	     "Radius server entry."
     INDEX { wwpRadiusServerId }
     ::= { wwpRadiusServerTable 1 }

 WwpRadiusServerEntry ::= SEQUENCE {
     wwpRadiusServerId                              Integer32,
     wwpRadiusServerIpAddr                          IpAddress,
     wwpRadiusServerAuthPort                        Integer32,
     wwpRadiusClientRoundTripTime                   TimeTicks,
     wwpRadiusClientAccessRequests                  Counter32,
     wwpRadiusClientAccessRetransmissions           Counter32,
     wwpRadiusClientAccessAccepts                   Counter32,
     wwpRadiusClientAccessRejects                   Counter32,
     wwpRadiusClientAccessChallenges                Counter32,
     wwpRadiusClientMalformedAccessResponses        Counter32,
     wwpRadiusClientBadAuthenticators               Counter32,
     wwpRadiusClientPendingRequests                   Gauge32,
     wwpRadiusClientTimeouts                        Counter32,
     wwpRadiusClientUnknownTypes                    Counter32,
     wwpRadiusClientPacketsDropped                  Counter32,
     wwpRadiusServerStatus                          RowStatus
 }

 wwpRadiusServerId  OBJECT-TYPE
     SYNTAX       Integer32(1..2147483647)
     MAX-ACCESS   read-only
     STATUS       current
     DESCRIPTION
	     "Index to the Radius Server Entry. The radius Servers are
             polled according to their ServerIds. If the ServerId 1
             doesn't respond, then it tries for the next and hence on."
     ::= { wwpRadiusServerEntry 1 }

 wwpRadiusServerIpAddr OBJECT-TYPE
     SYNTAX       IpAddress
     MAX-ACCESS   read-write
     STATUS       current
     DESCRIPTION
	     "IP Address of the RADIUS server."
     ::= { wwpRadiusServerEntry 2 }

 wwpRadiusServerAuthPort OBJECT-TYPE
      SYNTAX      Integer32 (1..65535)
      MAX-ACCESS  read-write
      STATUS      current
      DESCRIPTION
	      "The destination UDP port number to which RADIUS
	      messages should be sent.  The RADIUS server will not be
	      used for authentication if this port number is 0."
      DEFVAL { 1812 }
      ::= { wwpRadiusServerEntry 3 }

 wwpRadiusClientRoundTripTime  OBJECT-TYPE
      SYNTAX TimeTicks
      MAX-ACCESS read-only
      STATUS current
      DESCRIPTION
            "The time interval (in hundredths of a second) between
             the most recent Access-Reply/Access-Challenge and the
             Access-Request that matched it from this RADIUS
             authentication server."
      ::= { wwpRadiusServerEntry 4 }

-- Request/Response statistics
--
-- TotalIncomingPackets = Accepts + Rejects + Challenges + UnknownTypes
--
-- TotalIncomingPackets - MalformedResponses - BadAuthenticators -
-- UnknownTypes - PacketsDropped = Successfully received
--
-- AccessRequests + PendingRequests + ClientTimeouts =
-- Successfully Received
--
--

 wwpRadiusClientAccessRequests OBJECT-TYPE
      SYNTAX Counter32
      MAX-ACCESS read-only
      STATUS current
      DESCRIPTION
            "The number of RADIUS Access-Request packets sent
             to this server. This does not include retransmissions."
      ::= { wwpRadiusServerEntry 5 }

 wwpRadiusClientAccessRetransmissions OBJECT-TYPE
      SYNTAX Counter32
      MAX-ACCESS read-only
      STATUS current
      DESCRIPTION
            "The number of RADIUS Access-Request packets
             retransmitted to this RADIUS authentication server."
      ::= { wwpRadiusServerEntry 6 }

 wwpRadiusClientAccessAccepts OBJECT-TYPE
      SYNTAX Counter32
      MAX-ACCESS read-only
      STATUS current
      DESCRIPTION
            "The number of RADIUS Access-Accept packets
             (valid or invalid) received from this server."
      ::= { wwpRadiusServerEntry 7 }

 wwpRadiusClientAccessRejects OBJECT-TYPE
      SYNTAX Counter32
      MAX-ACCESS read-only
      STATUS current
      DESCRIPTION
            "The number of RADIUS Access-Reject packets
             (valid or invalid) received from this server."
      ::= { wwpRadiusServerEntry  8 }

 wwpRadiusClientAccessChallenges OBJECT-TYPE
      SYNTAX Counter32
      MAX-ACCESS read-only
      STATUS current
      DESCRIPTION
            "The number of RADIUS Access-Challenge packets
             (valid or invalid) received from this server."
      ::= { wwpRadiusServerEntry 9 }

 -- "Access-Response" includes an Access-Accept, Access-Challenge
 -- or Access-Reject

 wwpRadiusClientMalformedAccessResponses OBJECT-TYPE
      SYNTAX Counter32
      MAX-ACCESS read-only
      STATUS current
      DESCRIPTION
            "The number of malformed RADIUS Access-Response
             packets received from this server.
             Malformed packets include packets with
             an invalid length. Bad authenticators or
             Signature attributes or unknown types are not
             included as malformed access responses."
      ::= { wwpRadiusServerEntry 10 }

 wwpRadiusClientBadAuthenticators OBJECT-TYPE
      SYNTAX Counter32
      MAX-ACCESS read-only
      STATUS current
      DESCRIPTION
            "The number of RADIUS Access-Response packets
             containing invalid authenticators or Signature
             attributes received from this server."
      ::= { wwpRadiusServerEntry 11 }

 wwpRadiusClientPendingRequests OBJECT-TYPE
      SYNTAX Gauge32
      MAX-ACCESS read-only
      STATUS current
      DESCRIPTION
            "The number of RADIUS Access-Request packets
             destined for this server that have not yet timed out
             or received a response. This variable is incremented
             when an Access-Request is sent and decremented due to
             receipt of an Acess-Accept, Access-Reject or
             Access-Challenge, a timeout or retransmission."
      ::= { wwpRadiusServerEntry 12 }

 wwpRadiusClientTimeouts OBJECT-TYPE
     SYNTAX Counter32
     MAX-ACCESS read-only
     STATUS current
     DESCRIPTION
            "The number of authentication timeouts to this server.
             After a timeout the client may retry to the same
             server, send to a different server, or
             give up. A retry to the same server is counted as a
             retransmit as well as a timeout. A send to a different
             server is counted as a Request as well as a timeout."
      ::= { wwpRadiusServerEntry  13 }

 wwpRadiusClientUnknownTypes OBJECT-TYPE
      SYNTAX Counter32
      MAX-ACCESS read-only
      STATUS current
      DESCRIPTION
            "The number of RADIUS packets of unknown type which
             were received from this server on the authentication port."
      ::= { wwpRadiusServerEntry  14 }

 wwpRadiusClientPacketsDropped OBJECT-TYPE
      SYNTAX Counter32
      MAX-ACCESS read-only
      STATUS current
      DESCRIPTION
            "The number of RADIUS packets of which were
             received from this server on the authentication port
             and dropped for some other reason."
      ::= { wwpRadiusServerEntry  15 }

 wwpRadiusServerStatus OBJECT-TYPE
      SYNTAX        RowStatus
      MAX-ACCESS    read-create
      STATUS        current
      DESCRIPTION
            "To create a row in this table, a manager must
            set this object to either createAndGo(4).

            A row in the WwpRadiusServerEntry can't be set to active until
            wwpRadiusServerIpAddr has been set to valid value.

            To disable a Radius server , the operator can set this object
            to 'notInSerVice' state."
      ::= { wwpRadiusServerEntry 16 }


 wwpRadiusClientAuthKey OBJECT-TYPE
     SYNTAX        OCTET STRING (SIZE (8..127))
     MAX-ACCESS    read-write
     STATUS        current
     DESCRIPTION
	     "The Auth Key to be used for Radius Servers.
             Retrieving the value of this object via SNMP will
             return an empty string for security reasons."
     ::= { wwpRadiusClient 4 }

 END

 --
 -- WWP-RADIUS-CLIENT-MIB
 --
