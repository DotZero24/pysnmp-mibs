--
 -- WWP-VOIP-MIB.my
 --
 --

 WWP-VOIP-MIB DEFINITIONS ::= BEGIN

 IMPORTS
   IpAddress, Integer32, OBJECT-TYPE, MODULE-IDENTITY, NOTIFICATION-TYPE
	FROM SNMPv2-SMI
   DisplayString, MacAddress, TEXTUAL-CONVENTION
	FROM SNMPv2-TC
   wwpModules
	FROM WWP-SMI;


 wwpVoipMIB MODULE-IDENTITY
       LAST-UPDATED "200104031700Z"
       ORGANIZATION "World Wide Packets, Inc"
       CONTACT-INFO
	            "   Mib Meister
		        Postal: World Wide Packets
			P.O. Box 950
			Veradale, WA 99037
			USA
			Phone:  +1 509 242 9000
		  	Email:  mib.meister@worldwidepackets.com"
       DESCRIPTION
	       "This MIB module is for Voice Over IP feature
               on WWP Products"
       REVISION     "200104031700Z"
       DESCRIPTION
               "Initial creation."
	 ::= { wwpModules 15 }



 --
 -- Node definitions
 --

 wwpVoipMIBObjects OBJECT IDENTIFIER ::= { wwpVoipMIB 1 }

 wwpVoip OBJECT IDENTIFIER ::= { wwpVoipMIBObjects 1 }

  -- Notifications

 wwpVoipMIBNotificationPrefix  OBJECT IDENTIFIER ::= { wwpVoipMIB 2 }
 wwpVoipMIBNotifications       OBJECT IDENTIFIER ::=
                       { wwpVoipMIBNotificationPrefix 0 }

 -- Conformance information

 wwpVoipMIBConformance OBJECT IDENTIFIER ::= { wwpVoipMIB 3 }
 wwpVoipMIBCompliances OBJECT IDENTIFIER ::= { wwpVoipMIBConformance 1 }
 wwpVoipMIBGroups      OBJECT IDENTIFIER ::= { wwpVoipMIBConformance 2 }


 wwpVoipTable OBJECT-TYPE
     SYNTAX SEQUENCE OF WwpVoipEntry
     MAX-ACCESS     not-accessible
     STATUS         current
     DESCRIPTION
	     "The conceptual table listing all the Voice Over Ip Entries."
     ::= { wwpVoip 1 }

 wwpVoipEntry OBJECT-TYPE
     SYNTAX WwpVoipEntry
     MAX-ACCESS not-accessible
     STATUS     current
     DESCRIPTION
	"An entry in the wwpVoipTable."
     INDEX { wwpVoipIndex }
     ::= { wwpVoipTable 1 }

 WwpVoipEntry ::= SEQUENCE {
     wwpVoipIndex               INTEGER,
     wwpVoipDownLoaderVersion   DisplayString,
     wwpVoipApplicationVersion  DisplayString,
     wwpVoipPortNum             INTEGER,
     wwpVoipIpAddr              IpAddress,
     wwpVoipNumResets           Integer32,
     wwpVoipCallAgentAddr       IpAddress,
     wwpVoipResetOp             INTEGER
 }

 wwpVoipIndex  OBJECT-TYPE
     SYNTAX       INTEGER(1..65535)
     MAX-ACCESS   read-only
     STATUS       current
     DESCRIPTION
             "Index for the the Voip Entry."
     ::= { wwpVoipEntry 1 }

 wwpVoipDownLoaderVersion   OBJECT-TYPE
     SYNTAX       DisplayString
     MAX-ACCESS   read-only
     STATUS       current
     DESCRIPTION
             "The Downloader version for this VOIP entry."
     ::= { wwpVoipEntry 2 }

 wwpVoipApplicationVersion   OBJECT-TYPE
     SYNTAX       DisplayString
     MAX-ACCESS   read-only
     STATUS       current
     DESCRIPTION
             "The Aplication version for this VOIP entry."
     ::= { wwpVoipEntry 3 }

 wwpVoipPortNum   OBJECT-TYPE
     SYNTAX       INTEGER(1..65535)
     MAX-ACCESS   read-only
     STATUS       current
     DESCRIPTION
             "The Port Number for the VOIP."
     ::= { wwpVoipEntry 4 }

 wwpVoipIpAddr    OBJECT-TYPE
     SYNTAX       IpAddress
     MAX-ACCESS   read-only
     STATUS       current
     DESCRIPTION
             "The IP Address for the VOIP Entry."
     ::= { wwpVoipEntry 5 }

 wwpVoipNumResets OBJECT-TYPE
     SYNTAX          Integer32 (0..2147483647)
     MAX-ACCESS      read-only
     STATUS          current
     DESCRIPTION
	     "The number of times the VOIP processor has been reset."
     ::= { wwpVoipEntry 6 }

 wwpVoipCallAgentAddr OBJECT-TYPE
     SYNTAX          IpAddress
     MAX-ACCESS      read-only
     STATUS          current
     DESCRIPTION
	     "The IP address of the call agent to which this VOIP
             aplication is connected to."
     ::= { wwpVoipEntry 7 }

 wwpVoipResetOp     OBJECT-TYPE
     SYNTAX         INTEGER {
                         none(0),
                         reset(1)
                    }
     MAX-ACCESS     read-write
     STATUS         current
     DESCRIPTION
	     "This object reset the VOIP Aplication. A read on this object
              always returns 'none'."
     ::= { wwpVoipEntry 8 }


 wwpVoipDiagFailNotification NOTIFICATION-TYPE
	STATUS	current
	DESCRIPTION
		"A wwpVoipDiagFailNotification is sent if T2 VOIP ASIC fails
                diagnostics."
	::= { wwpVoipMIBNotifications 1 }


 END

 --
 -- WWP-VOIP-MIB.my
 --
