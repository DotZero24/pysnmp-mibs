--
 -- CIENA-CES-RSTP-MIB.my
 --
 --

 CIENA-CES-RSTP-MIB DEFINITIONS ::= BEGIN

 IMPORTS
   NOTIFICATION-TYPE, MODULE-IDENTITY
       FROM SNMPv2-SMI
   dot1dStpPort
            FROM BRIDGE-MIB
   dot1dStpPortOperEdgePort
            FROM RSTP-MIB
   cienaGlobalSeverity, cienaGlobalMacAddress
   		FROM CIENA-GLOBAL-MIB
   cienaCesPortPgIdMappingNotifChassisIndex, cienaCesPortPgIdMappingNotifShelfIndex, cienaCesPortPgIdMappingNotifSlotIndex,
   cienaCesPortPgIdMappingNotifPortNumber
   		FROM CIENA-CES-PORT-MIB
   cienaCesNotifications, cienaCesConfig
        FROM CIENA-SMI;


 cienaCesRstpMIB MODULE-IDENTITY
			LAST-UPDATED "201003280000Z"
			ORGANIZATION
				"Ciena Corp."
			CONTACT-INFO
        	"  Mib Meister
               115 North Sullivan Road
               Spokane Valley, WA 99037
               USA
               Phone:  +1 509 242 9000
               Email:  support@ciena.com"
	      DESCRIPTION
		       "This MIB module defines the mgmt objects and notifications
		        for the RSTP."

	      REVISION "201003280000Z"
	      DESCRIPTION
		       "Initial creation."
          ::= { cienaCesConfig 10}

 -- Notifications

 cienaCesRstpMIBNotificationPrefix  OBJECT IDENTIFIER ::= { cienaCesNotifications 10 }
 cienaCesRstpMIBNotifications    OBJECT IDENTIFIER ::=    { cienaCesRstpMIBNotificationPrefix 0 }

 -- Conformance information

 cienaCesRstpMIBConformance OBJECT IDENTIFIER ::= { cienaCesRstpMIB 2 }
 cienaCesRstpMIBCompliances OBJECT IDENTIFIER ::= { cienaCesRstpMIBConformance 1 }
 cienaCesRstpMIBGroups      OBJECT IDENTIFIER ::= { cienaCesRstpMIBConformance 2 }

 --
 -- Notifications
 --
 cienaCesRstpPortBackupNotification NOTIFICATION-TYPE
   OBJECTS  {  cienaGlobalSeverity,
   			   cienaGlobalMacAddress,
			   cienaCesPortPgIdMappingNotifChassisIndex,
			   cienaCesPortPgIdMappingNotifShelfIndex,
			   cienaCesPortPgIdMappingNotifSlotIndex,
			   cienaCesPortPgIdMappingNotifPortNumber,
           	   dot1dStpPort
      }
   STATUS   current
   DESCRIPTION
      "A cienaCesRstpPortBackupNotification is sent when the
      device detects a self loop (such as, the same cable connected to
      two ports on the same device). To enable the device to send this
      notification: cienaCesPortAllTrapState, cienaCesLogicalPortConfigPortAllTrapState
      for the port, and cienaCesRstpPortBackupTrapState must be set to enabled. These
      objects are set to enabled by default. Variable bindings include: cienaGlobalSeverity,
      cienaGlobalMacAddress, cienaCesPortPgIdMappingNotifChassisIndex,
      cienaCesPortPgIdMappingNotifShelfIndex, cienaCesPortPgIdMappingNotifSlotIndex,
      cienaCesPortPgIdMappingNotifPortNumber, and dot1dStpPort."
   ::= { cienaCesRstpMIBNotifications 1 }

 cienaCesRstpPvstBpduReceivedNotification NOTIFICATION-TYPE     -- RstpEvent_PortRcvdCiscoPvstBpdu
   OBJECTS  {  cienaGlobalSeverity,
   			   cienaGlobalMacAddress,
			   cienaCesPortPgIdMappingNotifChassisIndex,
			   cienaCesPortPgIdMappingNotifShelfIndex,
			   cienaCesPortPgIdMappingNotifSlotIndex,
			   cienaCesPortPgIdMappingNotifPortNumber,
           dot1dStpPort
      }
   STATUS   current
   DESCRIPTION
      "A cienaCesRstpPvstBpduReceivedNotification is sent when a PVST BPDU is received
      on the port. This trap is sent out every minute. To enable the device to send this
      notification: cienaCesPortAllTrapState, cienaCesLogicalPortConfigPortAllTrapState
      for the port, and cienaCesRstpPortPvstBPduReceivedTrapState must be set to enabled.
      These objects are set to enabled by default. Variable bindings include:
      cienaGlobalSeverity, cienaGlobalMacAddress, cienaCesPortPgIdMappingNotifChassisIndex,
      cienaCesPortPgIdMappingNotifShelfIndex, cienaCesPortPgIdMappingNotifSlotIndex,
      cienaCesPortPgIdMappingNotifPortNumber, and dot1dStpPort."
   ::= { cienaCesRstpMIBNotifications 2 }

 cienaCesRstpSelfLoopNotification NOTIFICATION-TYPE   --RstpEvent_LoopBackPortDetected
   OBJECTS  {  cienaGlobalSeverity,
   			   cienaGlobalMacAddress,
			   cienaCesPortPgIdMappingNotifChassisIndex,
			   cienaCesPortPgIdMappingNotifShelfIndex,
			   cienaCesPortPgIdMappingNotifSlotIndex,
			   cienaCesPortPgIdMappingNotifPortNumber,
           dot1dStpPort
      }
   STATUS   current
   DESCRIPTION
      "A cienaCesRstpSelfLoopNotification is sent when the device detects the same
      cable connected to a port in a loop back. Also, if loop-back blocking is enabled
      on the device, RSTP blocks this port (self disable). To enable the device to send
      this notification: cienaCesPortAllTrapState, cienaCesLogicalPortConfigPortAllTrapState
      for the port, and cienaCesRstpPortSelfLoopTrapState must be set to enabled. These
      are set to enabled by default. Variable bindings include: cienaGlobalSeverity,
      cienaGlobalMacAddress, cienaCesPortPgIdMappingNotifChassisIndex,
      cienaCesPortPgIdMappingNotifShelfIndex, cienaCesPortPgIdMappingNotifSlotIndex,
      cienaCesPortPgIdMappingNotifPortNumber, and dot1dStpPort."
   ::= { cienaCesRstpMIBNotifications 3 }

 cienaCesRstpPortOperEdgeNotification NOTIFICATION-TYPE     --RstpEvent_PortOperEdgePortChange
   OBJECTS  {  cienaGlobalSeverity,
   			   cienaGlobalMacAddress,
			   cienaCesPortPgIdMappingNotifChassisIndex,
			   cienaCesPortPgIdMappingNotifShelfIndex,
			   cienaCesPortPgIdMappingNotifSlotIndex,
			   cienaCesPortPgIdMappingNotifPortNumber,
           dot1dStpPort,
           dot1dStpPortOperEdgePort
      }
   STATUS   current
   DESCRIPTION
      "A cienaCesRstpPortOperEdgeNotification trap is sent when the device detects a port
      RSTP OperEdge change. To enable the device to send this notification:
      cienaCesPortAllTrapState, cienaCesLogicalPortConfigPortAllTrapState for the port,
      and cienaCesRstpPortOperEdgeTrapState must be set to enabled. These objects are set
      to enabled by default. Variable bindings include: cienaGlobalSeverity,
      cienaGlobalMacAddress, cienaCesPortPgIdMappingNotifChassisIndex,
      cienaCesPortPgIdMappingNotifShelfIndex, cienaCesPortPgIdMappingNotifSlotIndex,
      cienaCesPortPgIdMappingNotifPortNumber, dot1dStpPort, and dot1dStpPortOperEdgePort."
   ::= { cienaCesRstpMIBNotifications 4 }

 cienaCesRstpPortFlapNotification NOTIFICATION-TYPE   --RstpEvent_BridgePortFlapping or RstpEvent_PortStateUpdated  or RstpEvent_PortChangeUdate
   OBJECTS  {  cienaGlobalSeverity,
   			   cienaGlobalMacAddress,
			   cienaCesPortPgIdMappingNotifChassisIndex,
			   cienaCesPortPgIdMappingNotifShelfIndex,
			   cienaCesPortPgIdMappingNotifSlotIndex,
			   cienaCesPortPgIdMappingNotifPortNumber,
           dot1dStpPort
      }
   STATUS   current
   DESCRIPTION
      "A cienaCesRstpPortFlapNotification trap is sent when the device detects a port
      flapping. This trap is generated if the device detects that a port flapped more
      than once within 1 minute timer period and it has not sent trap within last 5
      minutes. To enable the device to send this notification: cienaCesPortAllTrapState,
      cienaCesLogicalPortConfigPortAllTrapState for the port, and
      cienaCesRstpPortFlapTrapState must be set to enable. These objects are set to
      enabled by default. Variable bindings include: cienaGlobalSeverity,
      cienaGlobalMacAddress, cienaCesPortPgIdMappingNotifChassisIndex,
      cienaCesPortPgIdMappingNotifShelfIndex, cienaCesPortPgIdMappingNotifSlotIndex,
      cienaCesPortPgIdMappingNotifPortNumber, and dot1dStpPort."
   ::= { cienaCesRstpMIBNotifications 5 }

 cienaCesRstpBridgeRootPortLostNotification NOTIFICATION-TYPE
   OBJECTS  {  cienaGlobalSeverity,
   			   cienaGlobalMacAddress,
			   cienaCesPortPgIdMappingNotifChassisIndex,
			   cienaCesPortPgIdMappingNotifShelfIndex,
			   cienaCesPortPgIdMappingNotifSlotIndex,
			   cienaCesPortPgIdMappingNotifPortNumber,
           dot1dStpPort
      }
   STATUS   current
   DESCRIPTION
      "A cienaCesRstpBridgeRootPortLostNotification trap is sent when the device detects
      that the bridge root port is lost. This trap indicates either the link failure or
      link partner RSTP disabled. To enable the device to send this notification:
      cienaCesPortAllTrapState, cienaCesLogicalPortConfigPortAllTrapState for the port, and
      cienaCesRstpBridgeRootPortLostTrapState must be set to enabled. These objects are set
      to enabled by default. Variable bindings include: cienaGlobalSeverity,
      cienaGlobalMacAddress, cienaCesPortPgIdMappingNotifChassisIndex,
      cienaCesPortPgIdMappingNotifShelfIndex, cienaCesPortPgIdMappingNotifSlotIndex,
      cienaCesPortPgIdMappingNotifPortNumber, and dot1dStpPort."
   ::= { cienaCesRstpMIBNotifications 6 }

 END

 --
 -- CIENA-CES-RSTP-MIB
 --
