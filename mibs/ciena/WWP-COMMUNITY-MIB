--
 -- WWP-COMMUNITY-MIB.my
 -- MIB generated by MG-SOFT Visual MIB Builder Version 2.1 Build 199
 -- Sunday, March 25, 2001 at 19:17:08
 --

 WWP-COMMUNITY-MIB DEFINITIONS ::= BEGIN

 IMPORTS
   IpAddress, Integer32, OBJECT-TYPE, MODULE-IDENTITY
	    FROM SNMPv2-SMI
   RowStatus, TEXTUAL-CONVENTION
	    FROM SNMPv2-TC
   wwpModules
	    FROM WWP-SMI;


 wwpCommunityMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP Community specific information."
	    REVISION    "200104031700Z"
	    DESCRIPTION
		    "Initial creation."
	    ::= { wwpModules 32 }

 --
 -- Node definitions
 --

 wwpCommunityMIBObjects OBJECT IDENTIFIER ::= { wwpCommunityMIB 1 }
 wwpCommunity OBJECT IDENTIFIER ::= { wwpCommunityMIBObjects 1 }


 -- Notifications

 wwpCommunityMIBNotificationPrefix  OBJECT IDENTIFIER ::= { wwpCommunityMIB 2 }
 wwpCommunityMIBNotifications    OBJECT IDENTIFIER ::=
                       { wwpCommunityMIBNotificationPrefix 0 }

 -- Conformance information

 wwpCommunityMIBConformance OBJECT IDENTIFIER ::= { wwpCommunityMIB 3 }
 wwpCommunityMIBCompliances OBJECT IDENTIFIER ::= { wwpCommunityMIBConformance 1 }
 wwpCommunityMIBGroups      OBJECT IDENTIFIER ::= { wwpCommunityMIBConformance 2 }


 wwpCommunityTable OBJECT-TYPE
     SYNTAX       SEQUENCE OF WwpCommunityEntry
     MAX-ACCESS   not-accessible
     STATUS       current
     DESCRIPTION
	     "Table of read/write Community entries."
     ::= { wwpCommunity 1 }

 wwpCommunityEntry OBJECT-TYPE
     SYNTAX       WwpCommunityEntry
     MAX-ACCESS   not-accessible
     STATUS       current
     DESCRIPTION
	     "An entry for each read/write community."
     INDEX { wwpCommunityName, wwpCommunityIpAddress }
     ::= { wwpCommunityTable 1 }

 WwpCommunityEntry ::= SEQUENCE {
     wwpCommunityName            OCTET STRING(SIZE(0..64)),
     wwpCommunityIpAddress       IpAddress,
     wwpCommunityRights          INTEGER,
     wwpCommunityStatus          RowStatus
 }


 wwpCommunityName OBJECT-TYPE
     SYNTAX       OCTET STRING(SIZE(0..64))
     MAX-ACCESS   read-only
     STATUS       current
     DESCRIPTION
	     "The Name of Community String."
     ::= { wwpCommunityEntry 1 }

 wwpCommunityIpAddress OBJECT-TYPE
    SYNTAX      IpAddress
    MAX-ACCESS  read-only
    STATUS      current
    DESCRIPTION
	    "The IP Address of the host(s) with access rights. A value of 0
            means that access is allowed to any host."
    ::= { wwpCommunityEntry 2 }

 wwpCommunityRights OBJECT-TYPE
     SYNTAX       INTEGER {
                     readOnly(1),
                     readWrite(2)
                  }
     MAX-ACCESS   read-write
     STATUS       current
     DESCRIPTION
	     "Rights associated with the Community Strings. The community Name
             associated with 'readOnly' community Rights will not have any
             access (read\write) to the readWrite communities."
     ::= { wwpCommunityEntry 3 }

 wwpCommunityStatus OBJECT-TYPE
     SYNTAX      RowStatus
     MAX-ACCESS  read-create
     STATUS      current
     DESCRIPTION
	     "To create a row in this table, a manager must
             set this object to 'createAndGo'. wwpCommunityRights
             must be valid prior to setting this object to 'active'.
             The Agent should not let all the comunities to be deleted
             as this will cause isolation of the device. At least one
             readOnly community and one readWrite community should always
             be present."
     ::= { wwpCommunityEntry 4 }

 wwpNotifCommunityTable OBJECT-TYPE
     SYNTAX       SEQUENCE OF WwpNotifCommunityEntry
     MAX-ACCESS   not-accessible
     STATUS       current
     DESCRIPTION
	     "Table of Notification Community entries."
     ::= { wwpCommunity 2 }

 wwpNotifCommunityEntry OBJECT-TYPE
     SYNTAX       WwpNotifCommunityEntry
     MAX-ACCESS   not-accessible
     STATUS       current
     DESCRIPTION
	     "An entry for each notification community."
     INDEX { wwpNotifCommunityName, wwpNotifCommunityDestAddr }
     ::= { wwpNotifCommunityTable 1 }

 WwpNotifCommunityEntry ::= SEQUENCE {
     wwpNotifCommunityName         OCTET STRING(SIZE(0..64)),
     wwpNotifCommunityDestAddr     IpAddress,
     wwpNotifCommunityStatus       RowStatus
 }


 wwpNotifCommunityName OBJECT-TYPE
     SYNTAX       OCTET STRING(SIZE(0..64))
     MAX-ACCESS   read-only
     STATUS       current
     DESCRIPTION
	     "The Community String to be used for the notifications."
     ::= { wwpNotifCommunityEntry 1 }

 wwpNotifCommunityDestAddr OBJECT-TYPE
    SYNTAX      IpAddress
    MAX-ACCESS  read-only
    STATUS      current
    DESCRIPTION
	    "The IP Address of the host to which notification is to be sent."
    ::= { wwpNotifCommunityEntry 2 }

 wwpNotifCommunityStatus OBJECT-TYPE
     SYNTAX      RowStatus
     MAX-ACCESS  read-create
     STATUS      current
     DESCRIPTION
	     "To create a row in this table, a manager must
             set this object to 'createAndGo'."
     ::= { wwpNotifCommunityEntry 3 }

 wwpCommunityPersist OBJECT-TYPE
      SYNTAX           INTEGER {
                         none(0),
                         persist(1)
                       }
      MAX-ACCESS       read-write
      STATUS           current
      DESCRIPTION
	      "To persist the SNMP communities, this object
              should be set to 'persist'.

             A read on this object should return none(0)."
       ::= { wwpCommunity  3 }


 END

 --
 -- WWP-COMMUNITY-MIB
 --
