--
 -- WWP-MAC-MGMT-MIB.my
 --
 --

 WWP-MAC-MGMT-MIB DEFINITIONS ::= BEGIN

 IMPORTS
	TEXTUAL-CONVENTION FROM SNMPv2-TC
   IpAddress, Integer32, OBJECT-TYPE, MODULE-IDENTITY
	    FROM SNMPv2-SMI
   MacAddress, RowStatus, TruthValue
	    FROM SNMPv2-TC
   wwpModules
	    FROM WWP-SMI;


 wwpMacMgmtMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
		DESCRIPTION
		    "Increased maximum value for SAC learn counts."
		REVISION   "200511221900Z" -- 22nd November. 2005
	    DESCRIPTION
		    "This MIB specifies the managed objects for Managing
                    the Mac addresses to the WWP products. This MIB is an
                    extension of the BRIDGE MIB."
            REVISION     "200304160000Z"  -- 14th April. 2003
	    DESCRIPTION
		    "As implementation of SAC is different for few of the
                    products, so added the new Sac Table."
	    REVISION    "200104031700Z"
	    DESCRIPTION
		    "Initial creation."
	    ::= { wwpModules 28 }


 --
 -- Textual conventions
 --

 VlanId ::= TEXTUAL-CONVENTION
    STATUS      current
    DESCRIPTION
        "A 12-bit VLAN ID used in the VLAN Tag header."
    SYNTAX      INTEGER (1..4094)

 --
 -- Node definitions
 --

 wwpMacMgmtMIBObjects OBJECT IDENTIFIER ::= { wwpMacMgmtMIB 1 }

 --
 -- System Atributes
 --
 wwpMacMgmt OBJECT IDENTIFIER ::= { wwpMacMgmtMIBObjects 1 }


 -- Notifications

 wwpMacMgmtMIBNotificationPrefix  OBJECT IDENTIFIER ::= { wwpMacMgmtMIB 2 }
 wwpMacMgmtMIBNotifications       OBJECT IDENTIFIER ::=
                       { wwpMacMgmtMIBNotificationPrefix 0 }

 -- Conformance information

 wwpMacMgmtMIBConformance OBJECT IDENTIFIER ::= { wwpMacMgmtMIB 3 }
 wwpMacMgmtMIBCompliances OBJECT IDENTIFIER ::= { wwpMacMgmtMIBConformance 1 }
 wwpMacMgmtMIBGroups      OBJECT IDENTIFIER ::= { wwpMacMgmtMIBConformance 2 }

 --
 --  The Mac Table
 --

 wwpMacMgmtMacTable OBJECT-TYPE
     SYNTAX     SEQUENCE OF WwpMacMgmtMacEntry
     MAX-ACCESS not-accessible
     STATUS     current
     DESCRIPTION
            "The (conceptual) table listing the mac addresses indexed by
            the Vlan, port and the macaddr."
    ::= { wwpMacMgmt 1 }

 wwpMacMgmtMacEntry OBJECT-TYPE
    SYNTAX     WwpMacMgmtMacEntry
    MAX-ACCESS not-accessible
    STATUS     current
    DESCRIPTION
            "An entry (conceptual row) in the wwpMacMgmtMacTable."
    INDEX      { wwpMacMgmtVlanID, wwpMacMgmtPortId, wwpMacMgmtMacAddr }
    ::= { wwpMacMgmtMacTable 1 }


 WwpMacMgmtMacEntry ::= SEQUENCE {
    wwpMacMgmtVlanID              VlanId,
    wwpMacMgmtPortId              INTEGER,
    wwpMacMgmtMacAddr             MacAddress,
    wwpMacMgmtMacAddrMode         INTEGER,
    wwpMacMgmtMacStatus           INTEGER,
    wwpMacMgmtMacRowStatus        RowStatus
 }



 wwpMacMgmtVlanID OBJECT-TYPE
     SYNTAX       VlanId
     MAX-ACCESS   read-only
     STATUS       current
     DESCRIPTION
             "The vlan id associated with  wwpMacMgmtMacAddr and
             the wwpMacMgmtPortId."
     ::= { wwpMacMgmtMacEntry 1 }

 wwpMacMgmtPortId OBJECT-TYPE
     SYNTAX     INTEGER(1..65535)
     MAX-ACCESS read-only
     STATUS     current
     DESCRIPTION
             "Port ID for the instance.  Port ID's start at 1, and are
	     consecutive for each additional port. This port Id should
             refer to the dot1dBasePort in the Dot1dBasePortEntry."
     ::= { wwpMacMgmtMacEntry 2 }

 wwpMacMgmtMacAddr OBJECT-TYPE
     SYNTAX     MacAddress
     MAX-ACCESS read-only
     STATUS     current
     DESCRIPTION
             "A unicast MAC address which has either been learned by
             the port or has been statically configured."
     ::= { wwpMacMgmtMacEntry 3 }


 wwpMacMgmtMacAddrMode OBJECT-TYPE
     SYNTAX            INTEGER {
                            dynamic(1),
                            static(2)
                       }
     MAX-ACCESS        read-write
     STATUS            current
     DESCRIPTION
             "The Mac Addr can be either dynamic or static.
             For the Static entries the aging time specified by
             dot1dTpAgingTime does not apply so they stay forever
             in the Mac Table unless mac table is flushed.
             Once the wwpMacMgmtStatus is set to 'active',
             the wwpMacMgmtMacAddrMode can't be modified."
     ::= { wwpMacMgmtMacEntry 4 }

 wwpMacMgmtMacStatus   OBJECT-TYPE
     SYNTAX           INTEGER {
                             enable(1),
                             disable(2)
                      }
     MAX-ACCESS       read-only
     STATUS           current
     DESCRIPTION
             "The Mac Address will be disabled or enabled depending upon
             the protective mode and its Mac Address limit. The added
             static Mac Address will always be enabled."
     ::= { wwpMacMgmtMacEntry 5 }

 wwpMacMgmtMacRowStatus OBJECT-TYPE
     SYNTAX            RowStatus
     MAX-ACCESS        read-create
     STATUS            current
     DESCRIPTION
	     "Used to manage the creation and deletion of the
	     conceptual rows in this table.

             To create a row in this table, a manager must
             set this object to 'createAndGo'.

             The RowStatus can't be set to active unless
             wwpMacMgmtMacAddrMode has a valid value."
     ::= { wwpMacMgmtMacEntry 6 }


 wwpMacMgmtMacReset OBJECT-TYPE
      SYNTAX         INTEGER  {
                         none(0),
                         reset(1)
                    }
     MAX-ACCESS     read-write
     STATUS         current
     DESCRIPTION
	     "To reset the Mac Table for all the ports. A read on
             this object will always return the 'none'."
     ::= { wwpMacMgmt 2 }

 --
 --  The Protected Mode Table
 --

 wwpMacMgmtPMTable OBJECT-TYPE
     SYNTAX     SEQUENCE OF WwpMacMgmtPMEntry
     MAX-ACCESS not-accessible
     STATUS     current
     DESCRIPTION
            "The (conceptual) table listing the protected mode attributes."
    ::= { wwpMacMgmt 3 }

 wwpMacMgmtPMEntry OBJECT-TYPE
    SYNTAX     WwpMacMgmtPMEntry
    MAX-ACCESS not-accessible
    STATUS     current
    DESCRIPTION
            "An entry (conceptual row) in the wwpMacMgmtPMTable."
    INDEX      { wwpMacMgmtPMVlanID, wwpMacMgmtPMPortId }
    ::= { wwpMacMgmtPMTable 1 }


 WwpMacMgmtPMEntry ::= SEQUENCE {
    wwpMacMgmtPMVlanID              VlanId,
    wwpMacMgmtPMPortId              INTEGER,
    wwpMacMgmtPMLearnLimit          INTEGER,
    wwpMacMgmtPMLearnCount          INTEGER,
    wwpMacMgmtPMStatus              INTEGER,
    wwpMacMgmtPMMacFlush            INTEGER
 }


 wwpMacMgmtPMVlanID OBJECT-TYPE
     SYNTAX        VlanId
     MAX-ACCESS    read-only
     STATUS        current
     DESCRIPTION
             "The vlan id associated with  wwpMacMgmtMacAddr and
             the wwpMacMgmtPortId."
     ::= { wwpMacMgmtPMEntry 1 }

 wwpMacMgmtPMPortId OBJECT-TYPE
     SYNTAX      INTEGER(1..65535)
     MAX-ACCESS  read-only
     STATUS      current
     DESCRIPTION
             "Port ID for the instance.  Port ID's start at 1, and are
	     consecutive for each additional port. This port Id should
             refer to the dot1dBasePort in the Dot1dBasePortEntry."
     ::= { wwpMacMgmtPMEntry 2 }

 wwpMacMgmtPMLearnLimit OBJECT-TYPE
     SYNTAX             INTEGER(0..24)
     MAX-ACCESS         read-write
     STATUS             current
     DESCRIPTION
             "The maximum number of Mac Addresses which will be learned by this
             Vlan/port pair. This limits applies only for the dynamic
             addresses."
     ::= { wwpMacMgmtPMEntry 3 }

 wwpMacMgmtPMLearnCount   OBJECT-TYPE
     SYNTAX           INTEGER(0..24)
     MAX-ACCESS       read-only
     STATUS           current
     DESCRIPTION
             "The number of Mac Addresses learned by this Vlan/Port pair.
             If the wwpMacMgmtMacStatus is enabled then the max value for
             this object should be equal to wwpMacMgmtPMLearnLimit."
     ::= { wwpMacMgmtPMEntry 4 }

 wwpMacMgmtPMStatus   OBJECT-TYPE
     SYNTAX           INTEGER {
                             enable(1),
                             disable(2)
                      }
     MAX-ACCESS       read-write
     STATUS           current
     DESCRIPTION
             "To enable the Protection Mode, wwpMacMgmtPMStatus should be set
             to enable."
     DEFVAL { disable }
     ::= { wwpMacMgmtPMEntry 5 }

 wwpMacMgmtPMMacFlush   OBJECT-TYPE
     SYNTAX           INTEGER {
                             none(0),
                             flush(1)
                      }
     MAX-ACCESS       read-write
     STATUS           current
     DESCRIPTION
             "Setting this object to 'flush' causes all the dynamic
             MAC entries for the port/vlan specified by
             wwpMacMgmtPMPortId/wwpMacMgmtPMVlanID to be deleted.
             An SNMP read on this object returns 'none' once the
             flush operation is completed."
     ::= { wwpMacMgmtPMEntry 6 }


 wwpMacMgmtCacheMac   OBJECT-TYPE
     SYNTAX      TruthValue
     MAX-ACCESS  read-write
     STATUS      current
     DESCRIPTION
             "Specifies whether or not the snmp Agent should cache the Macs in the
             wwpMacMgmtCacheTable or not. Once a static Mac is added then this object
             should be set to 'True' again to update the cache.If 'mac reset' or 'mac flush'
             is used and then the Management Station should set this object to true again
             to update the Mac Cache Table."
     DEFVAL { false }
     ::= { wwpMacMgmt 4 }


 --
 --  The Mac Cache Table
 --

 wwpMacMgmtCacheMacTable OBJECT-TYPE
     SYNTAX     SEQUENCE OF WwpMacMgmtCacheMacEntry
     MAX-ACCESS not-accessible
     STATUS     current
     DESCRIPTION
            "The (conceptual) table listing the mac addresses indexed by
            the Vlan, port and the Mac Index."
    ::= { wwpMacMgmt 5 }

 wwpMacMgmtCacheMacEntry OBJECT-TYPE
    SYNTAX     WwpMacMgmtCacheMacEntry
    MAX-ACCESS not-accessible
    STATUS     current
    DESCRIPTION
            "An entry (conceptual row) in the wwpMacMgmtCacheMacTable."
    INDEX      { wwpMacMgmtCVlanID, wwpMacMgmtCPortId, wwpMacMgmtCMacIndex }
    ::= { wwpMacMgmtCacheMacTable 1 }


 WwpMacMgmtCacheMacEntry ::= SEQUENCE {
    wwpMacMgmtCVlanID              VlanId,
    wwpMacMgmtCPortId              INTEGER,
    wwpMacMgmtCMacIndex            INTEGER,
    wwpMacMgmtCMacAddr             MacAddress,
    wwpMacMgmtCMacAddrMode         INTEGER,
    wwpMacMgmtCMacStatus           INTEGER
 }


 wwpMacMgmtCVlanID OBJECT-TYPE
     SYNTAX       VlanId
     MAX-ACCESS   read-only
     STATUS       current
     DESCRIPTION
             "The vlan id associated with  wwpMacMgmtCMacIndex and
             the wwpMacMgmtCPortId."
     ::= { wwpMacMgmtCacheMacEntry 1 }

 wwpMacMgmtCPortId OBJECT-TYPE
     SYNTAX     INTEGER(1..65535)
     MAX-ACCESS read-only
     STATUS     current
     DESCRIPTION
             "Port ID for the instance.  Port ID's start at 1, and are
	     consecutive for each additional port. This port Id should
             refer to the dot1dBasePort in the Dot1dBasePortEntry."
     ::= { wwpMacMgmtCacheMacEntry 2 }

 wwpMacMgmtCMacIndex OBJECT-TYPE
     SYNTAX     INTEGER(1..65535)
     MAX-ACCESS read-only
     STATUS     current
     DESCRIPTION
             "Index for this Mac Address."
     ::= { wwpMacMgmtCacheMacEntry 3 }

 wwpMacMgmtCMacAddr OBJECT-TYPE
     SYNTAX     MacAddress
     MAX-ACCESS read-only
     STATUS     current
     DESCRIPTION
             "A unicast MAC address which has either been learned by
             the port or has been statically configured."
     ::= { wwpMacMgmtCacheMacEntry 4 }


 wwpMacMgmtCMacAddrMode OBJECT-TYPE
     SYNTAX            INTEGER {
                            dynamic(1),
                            static(2)
                       }
     MAX-ACCESS        read-only
     STATUS            current
     DESCRIPTION
             "The Mac Addr can be either dynamic or static.
             For the Static entries the aging time specified by
             dot1dTpAgingTime does not apply so they stay forever
             in the Mac Table unless mac table is flushed.
             Once the wwpMacMgmtStatus is set to 'active',
             the wwpMacMgmtMacAddrMode can't be modified."
     ::= { wwpMacMgmtCacheMacEntry 5 }


 wwpMacMgmtCMacStatus   OBJECT-TYPE
     SYNTAX           INTEGER {
                             enable(1),
                             disable(2)
                      }
     MAX-ACCESS       read-only
     STATUS           current
     DESCRIPTION
             "The Mac Address will be disabled or enabled depending upon
             the protective mode and its Mac Address limit. The added
             static Mac Address will always be enabled."
     ::= { wwpMacMgmtCacheMacEntry 6 }


 --
 --  The Mac Cache Count Table
 --

 wwpMacMgmtCacheMacCountTable OBJECT-TYPE
     SYNTAX     SEQUENCE OF WwpMacMgmtCacheMacCountEntry
     MAX-ACCESS not-accessible
     STATUS     current
     DESCRIPTION
            "The (conceptual) table listing the mac addresses indexed by
            the Vlan and the port."
    ::= { wwpMacMgmt 6 }

 wwpMacMgmtCacheMacCountEntry OBJECT-TYPE
    SYNTAX     WwpMacMgmtCacheMacCountEntry
    MAX-ACCESS not-accessible
    STATUS     current
    DESCRIPTION
            "An entry (conceptual row) in the wwpMacMgmtCacheMacTable."
    INDEX      { wwpMacMgmtCVlanID, wwpMacMgmtCPortId }
    ::= { wwpMacMgmtCacheMacCountTable 1 }


 WwpMacMgmtCacheMacCountEntry ::= SEQUENCE {
      wwpMacMgmtCacheMacCount INTEGER
 }


 wwpMacMgmtCacheMacCount  OBJECT-TYPE
     SYNTAX     INTEGER(0..65535)
     MAX-ACCESS read-only
     STATUS     current
     DESCRIPTION
             "Count of Mac Addresses associated with this Cache Mac Entry.
             The count will be shown only for the Vlan/port combination which
             exists on the box."
     ::= { wwpMacMgmtCacheMacCountEntry  1 }

 --
 --  The Security Access Control Table
 --

 wwpMacMgmtSacTable OBJECT-TYPE
     SYNTAX     SEQUENCE OF WwpMacMgmtSacEntry
     MAX-ACCESS not-accessible
     STATUS     current
     DESCRIPTION
            "The (conceptual) table listing the security access
	     control attributes."
    ::= { wwpMacMgmt 7 }

 wwpMacMgmtSacEntry OBJECT-TYPE
    SYNTAX     WwpMacMgmtSacEntry
    MAX-ACCESS not-accessible
    STATUS     current
    DESCRIPTION
            "An entry (conceptual row) in the wwpMacMgmtSacTable."
    INDEX      { wwpMacMgmtSacVlanID, wwpMacMgmtSacPortId }
    ::= { wwpMacMgmtSacTable 1 }


 WwpMacMgmtSacEntry ::= SEQUENCE {
    wwpMacMgmtSacVlanID              VlanId,
    wwpMacMgmtSacPortId              INTEGER,
    wwpMacMgmtSacLearnCount          INTEGER,
    wwpMacMgmtSacMaxLearn            INTEGER,
    wwpMacMgmtSacLearnDisabled       TruthValue,
    wwpMacMgmtSacMacFlush            INTEGER,
    wwpMacMgmtSacStatus              RowStatus
 }

 wwpMacMgmtSacVlanID OBJECT-TYPE
     SYNTAX        VlanId
     MAX-ACCESS    read-only
     STATUS        current
     DESCRIPTION
             "The VLAN id for this SAC entry."
     ::= { wwpMacMgmtSacEntry 1 }

 wwpMacMgmtSacPortId OBJECT-TYPE
     SYNTAX      INTEGER(1..65535)
     MAX-ACCESS  read-only
     STATUS      current
     DESCRIPTION
             "Port ID for the instance.  Port ID's start at 1, and are
	     consecutive for each additional port. This port Id should
             refer to the dot1dBasePort in the Dot1dBasePortEntry."
     ::= { wwpMacMgmtSacEntry 2 }

 wwpMacMgmtSacLearnCount   OBJECT-TYPE
     SYNTAX           INTEGER(0..3000)
     MAX-ACCESS       read-only
     STATUS           current
     DESCRIPTION
             "The number of Mac Addresses learned by this Vlan/Port pair.
             If the wwpMacMgmtMacStatus is enabled then the max value for
             this object should be equal to wwpMacMgmtSacMaxLearn."
     ::= { wwpMacMgmtSacEntry 3 }

 wwpMacMgmtSacMaxLearn OBJECT-TYPE
     SYNTAX             INTEGER(0..3000)
     MAX-ACCESS         read-create
     STATUS             current
     DESCRIPTION
             "The maximum number of Mac Addresses which will be
             learned by this Vlan/port pair. This limits applies
             only for the dynamic addresses."
     ::= { wwpMacMgmtSacEntry 4 }

 wwpMacMgmtSacLearnDisabled   OBJECT-TYPE
     SYNTAX           TruthValue
     MAX-ACCESS       read-create
     STATUS           current
     DESCRIPTION
             "Setting this object to 'true' will cause
             the learning for the port/vlan pair to be
             shut off."
     DEFVAL { false }
     ::= { wwpMacMgmtSacEntry 5 }

 wwpMacMgmtSacMacFlush   OBJECT-TYPE
     SYNTAX           INTEGER {
                          none(0),
                          flush(1)
                      }
     MAX-ACCESS       read-create
     STATUS           current
     DESCRIPTION
             "Setting this object to 'flush' causes all the dynamic
             MAC entries for the port/vlan specified by
             wwpMacMgmtSacPortId/wwpMacMgmtSacVlanID to be deleted.
             An SNMP read on this object returns 'none' once the
             flush operation is completed."
     ::= { wwpMacMgmtSacEntry 6 }

 wwpMacMgmtSacStatus   OBJECT-TYPE
     SYNTAX       RowStatus
     MAX-ACCESS   read-create
     STATUS       current
     DESCRIPTION
	     "Used to manage the creation and deletion of the
	     conceptual rows in this table.

             To create a row in this table, a manager must
             set this object to 'createAndGo'.
             The SAC entry cab be disabled by setting this object
	     to 'notInService'"
     ::= { wwpMacMgmtSacEntry 7 }

 END

 --
 -- WWP-MAC-MGMT-MIB
 --
