--
 -- WWP-QOS-410-MIB.my
 --
 --


 WWP-QOS-410-MIB DEFINITIONS ::= BEGIN

 IMPORTS
	TEXTUAL-CONVENTION FROM SNMPv2-TC
   NOTIFICATION-TYPE, Counter32, Integer32, OBJECT-TYPE, MODULE-IDENTITY
	    FROM SNMPv2-SMI
   TruthValue, RowStatus
            FROM SNMPv2-TC
   wwpModules
	    FROM WWP-SMI;

 wwpQos410MIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP QOS specific information."
	    REVISION    "200104031700Z"
	    DESCRIPTION
		    "Initial creation."
	    ::= { wwpModules 29 }


 VlanId ::= TEXTUAL-CONVENTION
    STATUS      current
    DESCRIPTION
        "A 12-bit VLAN ID used in the VLAN Tag header."
    SYNTAX      INTEGER (1..4094)


 --
 -- Node definitions
 --

 wwpQos410MIBObjects OBJECT IDENTIFIER ::= { wwpQos410MIB 1 }

 wwpQos410 OBJECT IDENTIFIER ::= { wwpQos410MIBObjects 1 }


 -- Notifications

 wwpQos410NotificationPrefix     OBJECT IDENTIFIER ::= { wwpQos410MIB 2 }
 wwpQos410Notifications          OBJECT IDENTIFIER ::=
                       { wwpQos410NotificationPrefix 0 }

 -- Conformance information

 wwpQos410MIBConformance OBJECT IDENTIFIER ::= { wwpQos410MIB 3 }
 wwpQos410MIBCompliances OBJECT IDENTIFIER ::= { wwpQos410MIBConformance 1 }
 wwpQos410MIBGroups      OBJECT IDENTIFIER ::= { wwpQos410MIBConformance 2 }

 wwpQos410Table OBJECT-TYPE
     SYNTAX       SEQUENCE OF WwpQos410Entry
     MAX-ACCESS   not-accessible
     STATUS       current
     DESCRIPTION
	     "A Table of QOS per vlan per port Entries."
     ::= { wwpQos410 1 }

 wwpQos410Entry  OBJECT-TYPE
     SYNTAX       WwpQos410Entry
     MAX-ACCESS   not-accessible
     STATUS       current
     DESCRIPTION
	     "The QOS per vlan per port Entry in the Table."
     INDEX { wwpQos410VlanId, wwpQos410IngressPortId, wwpQos410EgressPortId }
     ::= { wwpQos410Table 1 }

 WwpQos410Entry ::= SEQUENCE {
     wwpQos410VlanId            VlanId,
     wwpQos410IngressPortId     INTEGER,
     wwpQos410EgressPortId      INTEGER,
     wwpQos410MinRateLimit      Integer32,
     wwpQos410MaxRateLimit      Integer32,
     wwpQos410QueueSize         INTEGER,
     wwpQos410Weight            INTEGER,
     wwpQos410RowStatus         RowStatus
  }


 wwpQos410VlanId       OBJECT-TYPE
     SYNTAX         VlanId
     MAX-ACCESS     read-only
     STATUS         current
     DESCRIPTION
	     "Vlan ID for this instance of QOS. This Vlan Id should refer to
             the  wwpVlanId in the WwpVlanEntry."
     ::= { wwpQos410Entry 1 }

 wwpQos410IngressPortId       OBJECT-TYPE
     SYNTAX         INTEGER (1..65535)
     MAX-ACCESS     read-only
     STATUS         current
     DESCRIPTION
	     "Ingress Port ID for this instance of. Port ID's start at 1, and are
	     consecutive for each additional port. This port Id should
             refer to the dot1dBasePort in the Dot1dBasePortEntry."
     ::= { wwpQos410Entry 2 }

 wwpQos410EgressPortId       OBJECT-TYPE
     SYNTAX         INTEGER (1..65535)
     MAX-ACCESS     read-only
     STATUS         current
     DESCRIPTION
	     "Egress Port ID for this instance of. Port ID's start at 1, and are
	     consecutive for each additional port. This port Id should
             refer to the dot1dBasePort in the Dot1dBasePortEntry."
     ::= { wwpQos410Entry 3 }

 wwpQos410MinRateLimit OBJECT-TYPE
     SYNTAX            Integer32(0..128000)
     UNITS             "kbps"
     MAX-ACCESS        read-write
     STATUS            current
     DESCRIPTION
	     "Bandwidth guaranteed for this QOS entry, specified in 64Kb/s increments.
             The maximum value for this object is 8Gb/s, if this egress port is
             the lead port of a link aggregation group.  The total of all QOS entries
             for this port cannot exceed the total bandwidth of the port or the set will
             fail."
     ::= { wwpQos410Entry 4 }

 wwpQos410MaxRateLimit  OBJECT-TYPE
     SYNTAX         Integer32(1..128000)
     UNITS          "kbps"
     MAX-ACCESS     read-write
     STATUS         current
     DESCRIPTION
	     "Bandwidth limit that cannot be exceeded by this QOS entry.
             The bandwidth is specified in 64Kb/s increments, with a maximum
             of 8Gb/s. The value specified cannot exceed the current bandwidth
             of the port. Values greater than 1 Gb/s can only be setup once a
             link agg group has been established."
     ::= { wwpQos410Entry 5 }

 wwpQos410QueueSize OBJECT-TYPE
     SYNTAX         INTEGER {
                        qSize16kb(1),
                        qSize32kb(2),
                        qSize64kb(3),
                        qSize128kb(4),
                        qSize256kb(5),
                        qSize512kb(6),
                        qSize1mb(7),
                        qSize2mb(8),
                        qSize4mb(9),
                        qSize8mb(10),
                        qSize16mb(11),
                        qSize32mb(12)
                     }
     MAX-ACCESS     read-write
     STATUS         current
     DESCRIPTION
	     "The size of the queue for this QOS entry."
     ::= { wwpQos410Entry 6 }


 wwpQos410Weight  OBJECT-TYPE
     SYNTAX         INTEGER { qw1(1),    qw2(2),    qw3(3),    qw4(4),    qw5(5),    qw6(6),    qw7(7),
                              qw8(8),    qw10(9),   qw12(10),  qw14(11),  qw16(12),  qw20(13),  qw24(14),
                              qw28(15),  qw32(16),  qw40(17),  qw48(18),  qw56(19),  qw64(20),  qw80(21),
                              qw96(22),  qw112(23), qw128(24), qw160(25), qw192(26), qw224(27), qw256(28),
                              qw320(29), qw384(30), qw448(31), qw512(32), qw640(33), qw768(34), qw896(35),
                              qw1024(36)
                            }
     MAX-ACCESS     read-write
     STATUS         current
     DESCRIPTION
	     "Value that is used to determine which QOS entries
             will receive the remaining bandwidth once Minimum
             Bandwidth requirements have been satisfied for all
             QOS entries. QOS entries with greater weight
             (smaller number) will receive a larger portion of this bandwidth."
     ::= { wwpQos410Entry 7 }


 wwpQos410RowStatus    OBJECT-TYPE
     SYNTAX         RowStatus
     MAX-ACCESS     read-create
     STATUS         current
     DESCRIPTION
	     "Used to manage the creation and deletion of the
	     conceptual rows in this table.

             To create a row in this table, a manager must
             set this object to 'createAndGo'."
     ::= { wwpQos410Entry 8 }

 wwpQos410StatsTable OBJECT-TYPE
     SYNTAX       SEQUENCE OF WwpQos410StatsEntry
     MAX-ACCESS   not-accessible
     STATUS       current
     DESCRIPTION
	     "A Table of QOS Stats per vlan per ingress/egress port Entries."
     ::= { wwpQos410 2 }


 wwpQos410StatsEntry  OBJECT-TYPE
     SYNTAX       WwpQos410StatsEntry
     MAX-ACCESS   not-accessible
     STATUS       current
     DESCRIPTION
	     "The QOS Stats per vlan per port Entry in the Table."
     INDEX { wwpQos410StatsVlanId, wwpQos410StatsIngressPortId, wwpQos410StatsEgressPortId }
     ::= { wwpQos410StatsTable 1 }

 WwpQos410StatsEntry ::= SEQUENCE {
     wwpQos410StatsVlanId           VlanId,
     wwpQos410StatsIngressPortId    INTEGER,
     wwpQos410StatsEgressPortId     INTEGER,
     wwpQos410StatsType             INTEGER,
     wwpQos410RxBytesHi             Counter32,
     wwpQos410RxBytesLo             Counter32
 }

 wwpQos410StatsVlanId       OBJECT-TYPE
     SYNTAX         VlanId
     MAX-ACCESS     read-only
     STATUS         current
     DESCRIPTION
	     "Vlan ID for this instance of QOS. This Vlan Id should refer to
             the  wwpVlanId in the WwpVlanEntry."
     ::= { wwpQos410StatsEntry 1 }

 wwpQos410StatsIngressPortId    OBJECT-TYPE
     SYNTAX         INTEGER (1..65535)
     MAX-ACCESS     read-only
     STATUS         current
     DESCRIPTION
	     "Ingress Port ID for this instance of .  Port ID's start at 1,
             and are consecutive for each additional port. This port Id should
             refer to the dot1dBasePort in the Dot1dBasePortEntry."
     ::= { wwpQos410StatsEntry 2 }

 wwpQos410StatsEgressPortId    OBJECT-TYPE
     SYNTAX         INTEGER (1..65535)
     MAX-ACCESS     read-only
     STATUS         current
     DESCRIPTION
	     "Egress Port ID for this instance of. Port ID's start at 1,
             and are consecutive for each additional port. This port Id should
             refer to the dot1dBasePort in the Dot1dBasePortEntry."
     ::= { wwpQos410StatsEntry 3 }

 wwpQos410StatsType OBJECT-TYPE
     SYNTAX         INTEGER {
                         accepted(1),
                         discarded(2)
                    }
     MAX-ACCESS     read-write
     STATUS         current
     DESCRIPTION
	     "Determines which type of bytes to count, accepted bytes or discarded bytes
             for this QOS entry. The default will count accepted bytes."
     DEFVAL { accepted }
     ::= { wwpQos410StatsEntry 4 }

 wwpQos410RxBytesHi    OBJECT-TYPE
     SYNTAX         Counter32
     MAX-ACCESS     read-only
     STATUS         current
     DESCRIPTION
	     "The number of bytes received for this QOS Entry.This counter
             represents the upper 32 bits of the counter value."
     ::= { wwpQos410StatsEntry 5 }

 wwpQos410RxBytesLo    OBJECT-TYPE
     SYNTAX         Counter32
     MAX-ACCESS     read-only
     STATUS         current
     DESCRIPTION
	     "The number of bytes received for this QOS Entry.This counter
             represents the lower 32 bits of the counter value."
     ::= { wwpQos410StatsEntry 6 }

 wwpQos410PriToQMapTable OBJECT-TYPE
     SYNTAX       SEQUENCE OF WwpQos410PriToQMapEntry
     MAX-ACCESS   not-accessible
     STATUS       current
     DESCRIPTION
	     "A Table of mapping of an RX-priority to a TX-queue."
     ::= { wwpQos410 3 }

 wwpQos410PriToQMapEntry  OBJECT-TYPE
     SYNTAX       WwpQos410PriToQMapEntry
     MAX-ACCESS   not-accessible
     STATUS       current
     DESCRIPTION
	     "The mapping Entry of an RX-priority to a TX-queue in the Table."
     INDEX { wwpQos410RxPriority }
     ::= { wwpQos410PriToQMapTable 1 }

 WwpQos410PriToQMapEntry ::= SEQUENCE {
     wwpQos410RxPriority        Integer32,
     wwpQos410TxPriQueue        Integer32
 }

 wwpQos410RxPriority  OBJECT-TYPE
     SYNTAX         Integer32(0..7)
     MAX-ACCESS     read-only
     STATUS         current
     DESCRIPTION
	     "The RX-prioroty value for this entry."
     ::= { wwpQos410PriToQMapEntry 1 }

 wwpQos410TxPriQueue   OBJECT-TYPE
     SYNTAX         Integer32(0..7)
     MAX-ACCESS     read-write
     STATUS         current
     DESCRIPTION
	     "The TX-priority-queue value for this entry."
     ::= { wwpQos410PriToQMapEntry 2 }

 wwpQos410PortTable OBJECT-TYPE
     SYNTAX       SEQUENCE OF WwpQos410PortEntry
     MAX-ACCESS   not-accessible
     STATUS       current
     DESCRIPTION
	     "A Table of QOS per port Entries."
     ::= { wwpQos410 4 }

 wwpQos410PortEntry  OBJECT-TYPE
     SYNTAX       WwpQos410PortEntry
     MAX-ACCESS   not-accessible
     STATUS       current
     DESCRIPTION
	     "The QOS per port Entry in the Table."
     INDEX { wwpQos410PortIndex }
     ::= { wwpQos410PortTable 1 }

 WwpQos410PortEntry ::= SEQUENCE {
     wwpQos410PortIndex          INTEGER,
     wwpQos410PortProvisionedBW  Integer32,
     wwpQos410PortTotalBW        Integer32
 }


 wwpQos410PortIndex     OBJECT-TYPE
     SYNTAX             INTEGER (1..65535)
     MAX-ACCESS         read-only
     STATUS             current
     DESCRIPTION
	     "Port ID for this instance of. Port ID's start at 1, and are
	     consecutive for each additional port. This port Id should
             refer to the dot1dBasePort in the Dot1dBasePortEntry."
     ::= { wwpQos410PortEntry 1 }

 wwpQos410PortProvisionedBW OBJECT-TYPE
     SYNTAX           Integer32 (0..2147483647)
     MAX-ACCESS       read-only
     STATUS           current
     DESCRIPTION
	     "Number of 64Kbps of bandwidth that is currently Provisioned for
             this port. This value is read-only and is updated each time a
             QOS entry is created for this port.  If the port is a member of
             a Link Agg group and is not the lead port the value will be zero."
     ::= { wwpQos410PortEntry 2 }

 wwpQos410PortTotalBW OBJECT-TYPE
     SYNTAX           Integer32 (0..2147483647)
     MAX-ACCESS       read-only
     STATUS           current
     DESCRIPTION
	     "Number of 64Kbps of bandwidth that make up this port's total
             bandwidth. This value is read-only and is updated each time a
             QOS entry is created for this port. If the port is a
             member of a Link Agg group and this is not the lead port the
             value will be zero."
     ::= { wwpQos410PortEntry 3 }


 wwpQos410PortProvisionedNotifEnabled OBJECT-TYPE
     SYNTAX      TruthValue
     MAX-ACCESS  read-write
     STATUS      current
     DESCRIPTION
             "This variable indicates whether the system
             generates the wwpQos410PortOverProvisionedTrap and
             wwpQos410PortUnderProvisionedTrap.
             A false value prevents this notifications
             from being generated by this system."
    DEFVAL { true }
    ::= { wwpQos410 5 }

 wwpQos410PortOverProvisionedTrap NOTIFICATION-TYPE
	OBJECTS	   {
                     wwpQos410PortIndex
		   }
	STATUS	   current
	DESCRIPTION
		"A wwpQos410PortOverProvisionedTrap notification is sent when the
                provisioned bandwidth exceeds the total bandwidth available
                for a port. This situation may also occur when changes in a
                link aggregation group (such as deleting a port from the group)
                decrease the total bandwidth or at the bootTime when the
                link aggregation groups are formed."
	::= { wwpQos410Notifications 1 }

 wwpQos410PortUnderProvisionedTrap NOTIFICATION-TYPE
	OBJECTS	   {
                     wwpQos410PortIndex
		   }
	STATUS	   current
	DESCRIPTION
		"A wwpQos410PortUnderProvisionedTrap notification is sent when the
                previously over-provisioned situation is resolved for a port."
	::= { wwpQos410Notifications 2 }

 END

 --
 -- WWP-QOS-410-MIB
 --
