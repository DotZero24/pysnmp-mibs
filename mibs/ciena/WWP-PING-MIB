--
-- WWP-PING-MIB.my
--
--

	WWP-PING-MIB DEFINITIONS ::= BEGIN

		IMPORTS
			IpAddress, Integer32, Counter32, OBJECT-TYPE, MODULE-IDENTITY
				FROM SNMPv2-SMI
			TruthValue, TEXTUAL-CONVENTION
				FROM SNMPv2-TC
			wwpModules
				FROM WWP-SMI;

		wwpPingMIB MODULE-IDENTITY
			LAST-UPDATED "200107031257Z"
			ORGANIZATION
				"Organization."
			CONTACT-INFO
				" Mib Meister
				  Postal: World Wide Packets
				  P.O. Box 950
				  Veradale, WA 99037
				  USA
			          Phone:  +1 509 242 9000
				  Email:  mib.meister@worldwidepackets.com"
			DESCRIPTION
				"The MIB for WWP Ping"
			REVISION "200107031257Z"
			DESCRIPTION
				"Initial Creation"
			::= { wwpModules 21 }


--
-- Textual conventions
--

		PingFailCause ::= TEXTUAL-CONVENTION
			STATUS current
			DESCRIPTION
				"Description."
			SYNTAX INTEGER
				{
				unknownHost(1),
				socketError(2),
				bindError(3),
				connectError(4),
				missingHost(5),
				asyncError(6),
				nonBlockError(7),
				mcastError(8),
				ttlError(9),
				mcastTtlError(10),
				outputError(11),
				unreachableError(12),
				isAlive(13),
				txRx(14),
				commandCompleted(15),
				noStatus(16),
				sendRecvMismatch(17)
				}

		PingState ::= TEXTUAL-CONVENTION
			STATUS current
			DESCRIPTION
				"Description."
			SYNTAX INTEGER
				{
				idle(1),
				pinging(2),
				pingComplete(3),
				failed(4)
				}


--
-- Node definitions
--

		wwpPingMIBObjects OBJECT IDENTIFIER ::= { wwpPingMIB 1 }

		wwpPingDelay OBJECT-TYPE
			SYNTAX Integer32 (0..100000)
			MAX-ACCESS read-write
			STATUS current
			DESCRIPTION
				"The object specifies the minimum amount of time to wait
                                before sending the next packet in a sequence after receiving a
                                response or declaring a timeout for a previous packet."
			::= { wwpPingMIBObjects 1 }

		wwpPingPacketSize OBJECT-TYPE
			SYNTAX Integer32 (1..1464)
			MAX-ACCESS read-write
			STATUS current
			DESCRIPTION
				"The size of the ping packets to send to the target."
			DEFVAL { 56 }
			::= { wwpPingMIBObjects 2 }

		wwpPingActivate OBJECT-TYPE
			SYNTAX TruthValue
			MAX-ACCESS read-write
			STATUS current
			DESCRIPTION
				"Ping can be activated by setting this object to true.
                                Once the ping operation is completed , the object is
                                set to 'false'. This object can be set to 'false'
                                by the Management Station to stop the ping."
			::= { wwpPingMIBObjects 3 }

		wwpPingAddress OBJECT-TYPE
			SYNTAX IpAddress
			MAX-ACCESS read-write
			STATUS current
			DESCRIPTION
				"The address of the device to be pinged. The default
                                 value should be of the loopback address."
			::= { wwpPingMIBObjects 4 }

		wwpPingPacketCount OBJECT-TYPE
			SYNTAX Integer32 (0..100000)
			MAX-ACCESS read-write
			STATUS current
			DESCRIPTION
				"Specifies the number of icmp requests to send to the target."
			::= { wwpPingMIBObjects 5 }

		wwpPingPacketTimeout OBJECT-TYPE
			SYNTAX Integer32 (0..100000)
			MAX-ACCESS read-write
			STATUS current
			DESCRIPTION
				"Specifies the amount of time to wait for a response to a
                                transmitted packet before declaring the packet 'dropped'."
			::= { wwpPingMIBObjects 6 }

		wwpPingSentPackets OBJECT-TYPE
			SYNTAX Counter32
			MAX-ACCESS read-only
			STATUS current
			DESCRIPTION
				"The number of ping packets that have been sent to the target."
			::= { wwpPingMIBObjects 8 }

		wwpPingReceivedPackets OBJECT-TYPE
			SYNTAX Counter32
			MAX-ACCESS read-only
			STATUS current
			DESCRIPTION
				"The number of ping packets that have been reveived from the target."
			::= { wwpPingMIBObjects 9 }

		wwpPingFailCause OBJECT-TYPE
			SYNTAX PingFailCause
			MAX-ACCESS read-only
			STATUS current
			DESCRIPTION
				"The result of the ping."
			::= { wwpPingMIBObjects 13 }

		wwpPingState OBJECT-TYPE
			SYNTAX PingState
			MAX-ACCESS read-only
			STATUS current
			DESCRIPTION
				"The state of the ping process.The state be pinging, idle,
                                complete or failed."
			DEFVAL { idle }
			::= { wwpPingMIBObjects 15 }

                wwpPingUntilStopped OBJECT-TYPE
                        SYNTAX     TruthValue
                        MAX-ACCESS  read-write
                        STATUS     current
                        DESCRIPTION
                                "setting this object to true prior to wwpPingActivate will
                                cause the device to ping the specified host until
                                wwpPingActivate is set to false. The object can't be
                                modified once the ping is active. The object returns to
                                'false' once the ping is halted."
                        DEFVAL { false }
			::= { wwpPingMIBObjects 16 }

	END

--
-- WWP-PING-MIB.my
--
