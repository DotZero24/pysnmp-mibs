--
 -- WWP-LAYER4-FILTER-MIB.my
 --
 --

 WWP-LAYER4-FILTER-MIB DEFINITIONS ::= BEGIN

 IMPORTS
   Counter32, Integer32, Unsigned32, OBJECT-TYPE, MODULE-IDENTITY
	FROM SNMPv2-SMI
   DisplayString, TEXTUAL-CONVENTION, RowStatus
	FROM SNMPv2-TC
   wwpModules
	FROM WWP-SMI;


 wwpLayer4FilterMIB MODULE-IDENTITY
	    LAST-UPDATED "200304111700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "This MIB module defines the mgmt objects to support
		    the layer 4 filtering on the WWP products."
	    REVISION    "200304111700Z"
	    DESCRIPTION
		    "Initial creation."
	    ::= { wwpModules 52 }

  --
 -- Textual conventions
 --

 PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING (SIZE (0..255))


 --
 -- Node definitions
 --

 wwpLayer4FilterMIBObjects OBJECT IDENTIFIER ::= { wwpLayer4FilterMIB 1 }

 wwpLayer4Filter  OBJECT IDENTIFIER ::= { wwpLayer4FilterMIBObjects 1 }


 -- Notifications

 wwpLayer4FilterMIBNotificationPrefix  OBJECT IDENTIFIER ::= { wwpLayer4FilterMIB 2 }
 wwpLayer4FilterMIBNotifications       OBJECT IDENTIFIER ::=
                       { wwpLayer4FilterMIBNotificationPrefix 0 }

 -- Conformance information

 wwpLayer4FilterMIBConformance OBJECT IDENTIFIER ::= { wwpLayer4FilterMIB 3 }
 wwpLayer4FilterMIBCompliances OBJECT IDENTIFIER ::= { wwpLayer4FilterMIBConformance 1 }
 wwpLayer4FilterMIBGroups      OBJECT IDENTIFIER ::= { wwpLayer4FilterMIBConformance 2 }

 wwpMaxLayer4Filters OBJECT-TYPE
    SYNTAX      Unsigned32
    MAX-ACCESS  read-only
    STATUS      current
    DESCRIPTION
            "The maximum number of Layer4 Filters that this device
            supports."
    ::= { wwpLayer4Filter 1 }

 wwpNumLayer4Filters OBJECT-TYPE
    SYNTAX      Unsigned32
    MAX-ACCESS  read-only
    STATUS      current
    DESCRIPTION
            "The current number of Layer4 Filters that are
            configured in this device."
    ::= { wwpLayer4Filter 2 }

 wwpLayer4FilterTable OBJECT-TYPE
     SYNTAX     SEQUENCE OF WwpLayer4FilterEntry
     MAX-ACCESS not-accessible
     STATUS     current
     DESCRIPTION
            "The (conceptual) table listing the config
	        parameters for the Layer 4 filter."
     ::= { wwpLayer4Filter 3 }

 wwpLayer4FilterEntry OBJECT-TYPE
     SYNTAX      WwpLayer4FilterEntry
     MAX-ACCESS  not-accessible
     STATUS      current
     DESCRIPTION
            "An entry (conceptual row) in the wwpLayer4FilterTable."
     INDEX { wwpLayer4FilterName }
     ::= { wwpLayer4FilterTable 1 }

 WwpLayer4FilterEntry ::=  SEQUENCE {
     wwpLayer4FilterName                OCTET STRING,
     wwpLayer4FilterProtocolNumber      INTEGER,
     wwpLayer4FilterSrcPort             Integer32,
     wwpLayer4FilterDstPort             Integer32,
     wwpLayer4FilterStatus              RowStatus
 }

 wwpLayer4FilterName OBJECT-TYPE
     SYNTAX      OCTET STRING (SIZE(1..32))
     MAX-ACCESS  read-only
     STATUS      current
     DESCRIPTION
            "The locally arbitrary, but unique identifier
	    associated with this wwpLayer4FilterEntry."
     ::= { wwpLayer4FilterEntry 1 }

 wwpLayer4FilterProtocolNumber OBJECT-TYPE
     SYNTAX      INTEGER (0..65535)
     MAX-ACCESS  read-create
     STATUS      current
     DESCRIPTION
            "The protocol number for the Layer 4 Filter.
            The list of protocol numbers are assigned by
            IANA."
     REFERENCE
         "RFC 1700"
     ::= { wwpLayer4FilterEntry 2 }

 wwpLayer4FilterSrcPort OBJECT-TYPE
     SYNTAX      Integer32(0..65535)
     MAX-ACCESS  read-create
     STATUS      current
     DESCRIPTION
            "The traffic addressed to the transport layer
	    source port specified by this object will
	    be blocked by this filter. A zero value
	    for this object will indicate that this object
	    should be ignored while applying the filter."
     ::= { wwpLayer4FilterEntry 3 }

 wwpLayer4FilterDstPort OBJECT-TYPE
     SYNTAX      Integer32(0..65535)
     MAX-ACCESS  read-create
     STATUS      current
     DESCRIPTION
            "The traffic addressed to the transport layer
	    destination port specified by this object will
	    be blocked by this filter. A zero value
	    for this object will indicate that this object
	    should be ignored while applying the filter."
     ::= { wwpLayer4FilterEntry 4 }

 wwpLayer4FilterStatus OBJECT-TYPE
     SYNTAX       RowStatus
     MAX-ACCESS   read-create
     STATUS       current
     DESCRIPTION
	    "Used to manage the creation and deletion of the
	    conceptual rows in this table.

            To create a row in this table, a manager must
            set this object to 'createAndGo'.

	    Until instances of all corresponding columns are
            appropriately configured, the value of the
            corresponding instance of the wwpLayer4FilterStatus
            column can't be set to 'active'.

            In particular, a newly created row cannot be made
            active until the corresponding instance of
            wwpLayer4FilterProtocol has been set.

	    None of the objects can be modified while the
	    value of this object is active(1)."
     ::= { wwpLayer4FilterEntry 5 }

 --
 --  The Filter Attach Table
 --

 wwpLayer4FilterAttachTable OBJECT-TYPE
     SYNTAX     SEQUENCE OF WwpLayer4FilterAttachEntry
     MAX-ACCESS not-accessible
     STATUS     current
     DESCRIPTION
            "The (conceptual) table listing the attachment of
	    created filters to the VLANs and ports.
	    If there is no entry atached with the filter, then
	    filter is virtually disabled."
    ::= { wwpLayer4Filter 4 }

 wwpLayer4FilterAttachEntry OBJECT-TYPE
     SYNTAX     WwpLayer4FilterAttachEntry
     MAX-ACCESS not-accessible
     STATUS     current
     DESCRIPTION
            "An entry (conceptual row) in the wwpLayer4FilterAttachTable."
    INDEX      { wwpLayer4FilterVid, wwpLayer4FilterName, wwpLayer4FilterAttachType }
    ::= { wwpLayer4FilterAttachTable 1 }


 WwpLayer4FilterAttachEntry ::= SEQUENCE {
    wwpLayer4FilterVid            INTEGER,
    wwpLayer4FilterAttachType     INTEGER,
    wwpLayer4FilterPortList       PortList,
    wwpLayer4FilterCounterId      Integer32,
    wwpLayer4FilterCount          Counter32,
    wwpLayer4FilterAttachStatus   RowStatus
 }

 wwpLayer4FilterVid   OBJECT-TYPE
     SYNTAX           INTEGER (0..4094)
     MAX-ACCESS       read-only
     STATUS           current
     DESCRIPTION
    	    "The vlan id to be associated with this ingress filter."
     ::= { wwpLayer4FilterAttachEntry 1 }

 wwpLayer4FilterAttachType OBJECT-TYPE
     SYNTAX      INTEGER {
		      deny(1),
		      allow(2)
		 }
     MAX-ACCESS  read-create
     STATUS      current
     DESCRIPTION
            "The attach type for this filter. Setting
	    this object to 'allow' will allow the traffic
	    specified by the filter name."
     DEFVAL { deny }
     ::= { wwpLayer4FilterAttachEntry 2 }

 wwpLayer4FilterPortList OBJECT-TYPE
     SYNTAX      PortList
     MAX-ACCESS  read-create
     STATUS      current
     DESCRIPTION
            "The set of ports on which this filter is to be applied."
     ::= { wwpLayer4FilterAttachEntry 3 }

 wwpLayer4FilterCounterId OBJECT-TYPE
     SYNTAX      Integer32 (0..15)
     MAX-ACCESS  read-create
     STATUS      current
     DESCRIPTION
            "The stats related to this filter will be stored in the
	    counter specified by this object."
     ::= { wwpLayer4FilterAttachEntry 4 }

 wwpLayer4FilterCount OBJECT-TYPE
     SYNTAX      Counter32
     MAX-ACCESS  read-only
     STATUS      current
     DESCRIPTION
            "The stats value in the counter specified by
	    the wwpLayer4FilterCounterId."
     ::= { wwpLayer4FilterAttachEntry 5 }

 wwpLayer4FilterAttachStatus OBJECT-TYPE
     SYNTAX       RowStatus
     MAX-ACCESS   read-create
     STATUS       current
     DESCRIPTION
	    "Used to manage the creation and deletion of the
	    conceptual rows in this table.

            To create a row in this table, a manager must
            set this object to 'createAndGo'.

	    Until instances of all corresponding columns are
            appropriately configured, the value of the
            corresponding instance of the wwpLayer4FilterStatus
            column can't be set to 'active'.

            In particular, a newly created row cannot be made
            active until the corresponding instance of
            wwpLayer4FilterPortList has been set.

	    None of the objects can be modified while the
	    value of this object is active(1)."
     ::= { wwpLayer4FilterAttachEntry 6 }

 END
