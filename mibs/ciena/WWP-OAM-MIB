--
-- WWP-OAM-MIB.my
-- MIB generated by MG-SOFT Visual MIB Builder Version 6.0  Build 88
-- Friday, August 26, 2005 at 18:21:04
--

	WWP-OAM-MIB DEFINITIONS ::= BEGIN

		IMPORTS
			OBJECT-GROUP, NOTIFICATION-GROUP
				FROM SNMPv2-CONF
			Counter64, Integer32, Unsigned32, Counter32, OBJECT-TYPE,
			MODULE-IDENTITY
				FROM SNMPv2-SMI
			TimeStamp
       			FROM SNMPv2-TC
			wwpModules
				FROM WWP-SMI;


		-- 1.3.6.1.4.1.6141.2.400
		wwpOamMibModule MODULE-IDENTITY
			LAST-UPDATED "200508191252Z"		-- August 19, 2005 at 12:52 GMT
			ORGANIZATION "World Wide Packets, Inc"
			CONTACT-INFO
				 "   Mib Meister
		  		Postal: World Wide Packets
				P.O. Box 950
				Veradale, WA 99037
				USA
		 		Phone:  +1 509 242 9000
				Email:  mib.meister@worldwidepackets.com"
			DESCRIPTION
				"The MIB module for managing the new Ethernet OAM features
				         introduced by the Ethernet in the First Mile task force (IEEE
				         802.3ah).  The functionality presented here is based on IEEE
				         802.3ah [802.3ah], released in October, 2004.

				         In particular, this MIB focused on the changes to Clause 30 of
				         the draft that are not specific to any physical layer.  These
				         changes are primarily reflected in the new OAM features
				         developed under this project, that can be applied to any
				         Ethernet like interface. The OAM features are described in
				         Clause 57 of [802.3ah].

				         The following reference is used throughout this MIB module:

				           [802.3ah] refers to:
				             IEEE Std 802.3ah-2004: 'Draft amendment to -
				             Information technology - Telecommunications and
				             information exchange between systems - Local and
				             metropolitan are networks - Specific requirements - Part
				             3: Carrier sense multiple access with collision detection
				             (CSMA/CD) access method and physical layer specifications
				             - Media Access Control Parameters, Physical Layers and
				             Management Parameters for subscriber access networks',
				             October 2004.

				           [802-2001] refers to:
				             'IEEE Standard for LAN/MAN (Local Area
				             Network/Metropolitan Area Network): Overview and
				             Architecture', IEEE 802, June 2001.

				         Copyright (c) The Internet Society (2005). This version of
				         this MIB module is part of RFC XXXX; See the RFC itself for
				         full legal notices."
			::= { wwpModules 400 }



--
-- Node definitions
--

		-- 1.3.6.1.4.1.6141.2.400.1
		wwpOamMIB OBJECT IDENTIFIER ::= { wwpOamMibModule 1 }


		-- 1.3.6.1.4.1.6141.2.400.1.1
		wwpOamConf OBJECT IDENTIFIER ::= { wwpOamMIB 1 }


		-- 1.3.6.1.4.1.6141.2.400.1.1.1
		wwpOamGroups OBJECT IDENTIFIER ::= { wwpOamConf 1 }



		-- 1.3.6.1.4.1.6141.2.400.1.1.2
		wwpOamCompls OBJECT IDENTIFIER ::= { wwpOamConf 2 }


		-- 1.3.6.1.4.1.6141.2.400.1.2
		wwpOamObjs OBJECT IDENTIFIER ::= { wwpOamMIB 2 }


		-- 1.3.6.1.4.1.6141.2.400.1.2.1
		wwpOamTable OBJECT-TYPE
			SYNTAX SEQUENCE OF WwpOamEntry
			MAX-ACCESS not-accessible
			STATUS current
			DESCRIPTION
				"Primary controls and status for the OAM capabilities of an
				         Ethernet like interface.  There will be one row in this table
				         for each Ethernet like interface in the system that supports
				         the Ethernet OAM functions defined in [802.3ah]."
			::= { wwpOamObjs 1 }


		-- 1.3.6.1.4.1.6141.2.400.1.2.1.1
		wwpOamEntry OBJECT-TYPE
			SYNTAX WwpOamEntry
			MAX-ACCESS not-accessible
			STATUS current
			DESCRIPTION
				"Description."
			INDEX { wwpOamPort }
			::= { wwpOamTable 1 }


		WwpOamEntry ::=
			SEQUENCE {
				wwpOamAdminState
					INTEGER,
				wwpOamOperStatus
					INTEGER,
				wwpOamMode
					INTEGER,
				wwpMaxOamPduSize
					Integer32,
				wwpOamConfigRevision
					Unsigned32,
				wwpOamFunctionsSupported
					BITS,
				wwpOamPort
					Integer32
			 }

		-- 1.3.6.1.4.1.6141.2.400.1.2.1.1.1
		wwpOamAdminState OBJECT-TYPE
			SYNTAX INTEGER
				{
				disabled(1),
				enabled(2)
				}
			MAX-ACCESS read-write
			STATUS current
			DESCRIPTION
				"This object is used to provision the default administrative OAM mode for this
				interface.  This object represents the desired state of OAM for this interface.

				The wwpOamAdminState always starts in the disabled(1) state
				         until an explicity management action or configuration
				         information retained by the system causes a transition to the
				         enabled(2) state.

				         Note that the value of this object is ignored when the
				         interface is not operating in full-duplex mode. OAM is not
				         supported on half-duplex links."
			::= { wwpOamEntry 1 }


		-- 1.3.6.1.4.1.6141.2.400.1.2.1.1.2
		wwpOamOperStatus OBJECT-TYPE
			SYNTAX INTEGER
				{
				disabled(1),
				linkfault(2),
				passiveWait(3),
				activeSendLocal(4),
				sendLocalAndRemote(5),
				sendLocalAndRemoteOk(6),
				oamPeeringLocallyRejected(7),
				oamPeeringRemotelyRejected(8),
				operational(9)
				}
			MAX-ACCESS read-only
			STATUS current
			DESCRIPTION
				"At initialization and failure conditions, two OAM entities on
				         the same full-duplex Ethernet link begin a discovery phase to
				         determine what OAM capabilities may be used on that link.  The
				         progress of this initialization is controlled by the OAM
				         sublayer.

				         This value is always disabled(1) if OAM is disabled on this
				         interface via the wwpOamAdminState.

				         If the link has detected a fault and is transmitting OAMPDUs
				         with a link fault indication, the value is linkFault(2).

				         The passiveWait(3) state is returned only by OAM entities in
				         passive mode (wwpOamMode) and reflects the state in which the
				         OAM entity is waiting to see if the peer device is OAM
				         capable.  The activeSendLocal(4) is used by active mode
				         devices (wwpOamMode) and reflects the OAM entity actively
				         trying to discover whether the peer has OAM capability but has
				         not yet made that determination.

				         The state sendLocalAndRemote(5) reflects that the local OAM
				         entity has discovered the peer but has not yet accepted or
				         rejected the configuration of the peer.  The local device can,
				         for whatever reason, decide that the peer device is
				         unacceptable and decline OAM peering.  If the local OAM entity
				         rejects the peer OAM entity, the state becomes
				         oamPeeringLocallyRejected(7).  If the OAM peering is allowed
				         by the local device, the state moves to
				         sendLocalAndRemoteOk(6).  Note that both the
				         sendLocalAndRemote(5) and oamPeeringLocallyRejected(7) states
				         fall within the state SEND_LOCAL_REMOTE of the Discovery state
				         diagram [802.3ah, Figure 57-5], with the difference being
				         whether the local OAM client has actively rejected the peering
				         or has just not indicated any decision yet.  Whether a peering
				         decision has been made is indicated via the local flags field
				         in the OAMPDU (reflected in the aOAMLocalFlagsField of
				         30.3.6.1.10).

				         If the remote OAM entity rejects the peering, the state
				         becomes oamPeeringRemotelyRejected(8).  Note that both the
				         sendLocalAndRemoteOk(6) and oamPeeringRemotelyRejected(8)
				         states fall within the state SEND_LOCAL_REMOTE_OK of the
				         Discovery state diagram [802.3ah, Figure 57-5], with the
				         difference being whether the remote OAM client has rejected
				         the peering or has just not yet decided.  This is indicated
				         via the remote flags field in the OAM PDU (reflected in the
				         aOAMRemoteFlagsField of 30.3.6.1.11).

				         When the local OAM entity learns that both it and the remote
				         OAM entity have accepted the peering, the state moves to
				         operational(9) corresponding to the SEND_ANY state of the
				         Discovery state diagram [802.3ah, Figure 57-5]. "
			::= { wwpOamEntry 2 }


		-- 1.3.6.1.4.1.6141.2.400.1.2.1.1.3
		wwpOamMode OBJECT-TYPE
			SYNTAX INTEGER
				{
				active(1),
				passive(2)
				}
			MAX-ACCESS read-write
			STATUS current
			DESCRIPTION
				"This object configures the mode of OAM operation for this
				         Ethernet like interface.  OAM on Ethernet interfaces may be in
				         'active' mode or 'passive' mode.  These two modes differ in
				         that active mode provides additional capabilities to initiate
				         monitoring activities with the remote OAM peer entity, while
				         passive mode generally waits for the peer to initiate OAM
				         actions with it.  As an example, an active OAM entity can put
				         the remote OAM entity in a loopback state, where a passive OAM
				         entity cannot.

				         The default value of wwpOamMode is dependent on the type of
				         system on which this Ethernet like interface resides.  The
				         default value should be 'active(1)' unless it is known that
				         this system should take on a subservient role to the other
				         device connected over this interface.

				         Changing this value results in incrementing the configuration
				         revision field of locally generated OAMPDUs (30.3.6.1.12) and
				         potentially re-doing the OAM discovery process if the
				         wwpOamOperStatus was already operational(9). "
			::= { wwpOamEntry 3 }


		-- 1.3.6.1.4.1.6141.2.400.1.2.1.1.4
		wwpMaxOamPduSize OBJECT-TYPE
			SYNTAX Integer32
			UNITS "bytes"
			MAX-ACCESS read-only
			STATUS current
			DESCRIPTION
				"The largest OAMPDU that the OAM entity supports.  OAM
				         entities exchange maximum OAMPDU sizes and negotiate to use
				         the smaller of the two maximum OAMPDU sizes between the peers.
				         This value is determined by the local implementation."
			::= { wwpOamEntry 4 }


		-- 1.3.6.1.4.1.6141.2.400.1.2.1.1.5
		wwpOamConfigRevision OBJECT-TYPE
			SYNTAX Unsigned32
			MAX-ACCESS read-only
			STATUS current
			DESCRIPTION
				"The configuration revision of the OAM entity as reflected in
				         the latest OAMPDU sent by the OAM entity.  The config revision
				         is used by OAM entities to indicate configuration changes have
				         occured which might require the peer OAM entity to re-evaluate
				         whether the peering is allowed.  See local_satisfied in
				         [802.3ah, 57.3.1.2]."
			::= { wwpOamEntry 5 }


		-- 1.3.6.1.4.1.6141.2.400.1.2.1.1.6
		wwpOamFunctionsSupported OBJECT-TYPE
			SYNTAX BITS
				{
				unidirectionalSupport(0),
				loopbackSupport(1),
				eventSupport(2),
				variableSupport(3)
				}
			MAX-ACCESS read-only
			STATUS current
			DESCRIPTION
				"The OAM functions supported on this Ethernet like interface.
				         OAM consists of separate functional sets beyond the basic
				         discovery process which is always required.  These functional
				         groups can be supported independently by any implementation.
				         These values are communicated to the peer via the local
				         configuration field of Information OAMPDUs. "
			::= { wwpOamEntry 6 }


		-- 1.3.6.1.4.1.6141.2.400.1.2.1.1.7
		wwpOamPort OBJECT-TYPE
			SYNTAX Integer32 (1..1000)
			MAX-ACCESS read-only
			STATUS current
			DESCRIPTION
				"An Ethernet port on the switch."
			::= { wwpOamEntry 7 }


		-- 1.3.6.1.4.1.6141.2.400.1.2.2
		wwpOamPeerTable OBJECT-TYPE
			SYNTAX SEQUENCE OF WwpOamPeerEntry
			MAX-ACCESS not-accessible
			STATUS current
			DESCRIPTION
				"Information about the OAM peer for a particular Ethernet like
				         interface. OAM entities communicate with a single OAM peer
				         entity on full-duplex Ethernet links on which OAM is enabled
				         and operating properly.

				         In certain states, the OAM peer information is not available.
				         Whether peer information is available is communicated via the
				         wwpOamPeerStatus object.  When this object is inactive, all
				         other information in the row is to be considered invalid."
			::= { wwpOamObjs 2 }


		-- 1.3.6.1.4.1.6141.2.400.1.2.2.1
		wwpOamPeerEntry OBJECT-TYPE
			SYNTAX WwpOamPeerEntry
			MAX-ACCESS not-accessible
			STATUS current
			DESCRIPTION
				"An entry in the table, containing information on the peer OAM
				         entity for a single Ethernet like interface.

				         Note that there is at most one OAM peer for each Ethernet like
				         interface.  There is exactly one row in this table for each
				         Ethernet like interface supporting OAM. "
			INDEX { wwpOamLocalPort }
			::= { wwpOamPeerTable 1 }


		WwpOamPeerEntry ::=
			SEQUENCE {
				wwpOamPeerStatus
					INTEGER,
				wwpOamPeerMacAddress
					OCTET STRING(SIZE(6)),
				wwpOamPeerVendorOui
					OCTET STRING(SIZE(3)),
				wwpOamPeerVendorInfo
					Unsigned32,
				wwpOamPeerMode
					INTEGER,
				wwpOamPeerMaxOamPduSize
					Integer32,
				wwpOamPeerConfigRevision
					Unsigned32,
				wwpOamPeerFunctionsSupported
					BITS,
				wwpOamLocalPort
					Integer32
			 }

		-- 1.3.6.1.4.1.6141.2.400.1.2.2.1.1
		wwpOamPeerStatus OBJECT-TYPE
			SYNTAX INTEGER
				{
				active(1),
				inactive(2)
				}
			MAX-ACCESS read-only
			STATUS current
			DESCRIPTION
				"This object indicates whether the information in this row
				         should be considered valid.  When active(1), the information
				         is valid and represents the current peer of the OAM entity.
				         When inactive(2), the information in this row is invalid.

				         A value of inactive(2) is returned if the wwpOamOperStatus is
				         disabled, passiveWait, or activeSendLocal.  For all other
				         values of wwpOamOperStatus, a value of active(1) is returned."
			::= { wwpOamPeerEntry 1 }


		-- 1.3.6.1.4.1.6141.2.400.1.2.2.1.2
		wwpOamPeerMacAddress OBJECT-TYPE
			SYNTAX OCTET STRING(SIZE(6))
			MAX-ACCESS read-only
			STATUS current
			DESCRIPTION
				"The MAC address of the peer OAM entity.  The MAC address is
				         derived from the most recently received OAMPDU.  This value is
				         initialized to all zeros (0x000000000000).  This value is
				         invalid if the wwpOamPeerStatus is inactive.

				         An OAMPDU is indicated by a valid frame with (1) destination
				         MAC address equal to that of the reserved MAC address for Slow
				         Protocols (See 43B of [802.3ah]), (2) a lengthOrType field
				         equal to the reserved type for Slow Protocols, (3) and a Slow
				         Protocols subtype equal to that of the subtype reserved for
				         OAM."
			::= { wwpOamPeerEntry 2 }


		-- 1.3.6.1.4.1.6141.2.400.1.2.2.1.3
		wwpOamPeerVendorOui OBJECT-TYPE
			SYNTAX OCTET STRING(SIZE(3))
			MAX-ACCESS read-only
			STATUS current
			DESCRIPTION
				"The OUI of the OAM peer as reflected in the latest
				         Information OAMPDU received with a Local Information TLV.  The
				         OUI can be used to identify the vendor of the remote OAM
				         entity.  This value is initialized to all zeros (0x000000).
				         This value is considered invalid if the wwpOamPeerStatus is
				         inactive.

				         An Information OAMPDU is indicated by a valid frame with (1)
				         destination MAC address equal to that of the reserved MAC
				         address for Slow Protocols (See 43B of [802.3ah]), (2) a
				         lengthOrType field equal to the reserved type for Slow Protocols, (3) a Slow Protocols subtype equal to that of the
				         subtype reserved for OAM, (4) a OAM code that equals the code
				         reserved for Information OAMPDUs."
			::= { wwpOamPeerEntry 3 }


		-- 1.3.6.1.4.1.6141.2.400.1.2.2.1.4
		wwpOamPeerVendorInfo OBJECT-TYPE
			SYNTAX Unsigned32
			MAX-ACCESS read-only
			STATUS current
			DESCRIPTION
				"The Vendor Info of the OAM peer as reflected in the latest
				         Information OAMPDU received with a Local Information TLV.  The
				         vendor information field is within the Local Information TLV,
				         and can be used to determine additional information about the
				         peer entity.  The format of the vendor information is
				         unspecified within the 32-bit field.  This value is intialized
				         to all zeros (0x00000000).  This value is invalid if the
				         wwpOamPeerStatus is inactive.

				         An Information OAMPDU is indicated by a valid frame with (1)
				         destination MAC address equal to that of the reserved MAC
				         address for Slow Protocols (See 43B of [802.3ah]), (2) a
				         lengthOrType field equal to the reserved type for Slow
				         Protocols, (3) a Slow Protocols subtype equal to that of the
				         subtype reserved for OAM, and (4) a OAM code that equals the
				         code reserved for Information OAMPDUs. "
			::= { wwpOamPeerEntry 4 }


		-- 1.3.6.1.4.1.6141.2.400.1.2.2.1.5
		wwpOamPeerMode OBJECT-TYPE
			SYNTAX INTEGER
				{
				active(1),
				passive(2),
				unknown(3)
				}
			MAX-ACCESS read-only
			STATUS current
			DESCRIPTION
				"The mode of the OAM peer as reflected in the latest
				         Information OAMPDU received with a Local Information TLV.  The
				         mode of the peer can be determined from the Configuration
				         field in the Local Information TLV of the last Information
				         OAMPDU received from the peer.  This value is initialized to
				         unknown(3), and is not valid if the wwpOamPeerStatus is
				         inactive.

				         An Information OAMPDU is indicated by a valid frame with (1)
				         destination MAC address equal to that of the reserved MAC
				         address for Slow Protocols (See 43B of [802.3ah]), (2) a
				         lengthOrType field equal to the reserved type for Slow
				         Protocols, (3) a Slow Protocols subtype equal to that of the
				         subtype reserved for OAM, and (4) a OAM code that equals the
				         code reserved for Information OAMPDUs."
			::= { wwpOamPeerEntry 5 }


		-- 1.3.6.1.4.1.6141.2.400.1.2.2.1.6
		wwpOamPeerMaxOamPduSize OBJECT-TYPE
			SYNTAX Integer32
			UNITS "bytes"
			MAX-ACCESS read-only
			STATUS current
			DESCRIPTION
				"The maximum size of OAMPDU supported by the peer as reflected
				         in the latest Information OAMPDU received with a Local
				         Information TLV.   Ethernet OAM on this interface must not use
				         OAMPDUs that exceed this size.  The maximum OAMPDU size can be
				         determined from the PDU Configuration field of the Local
				         Information TLV of the last Information OAMPDU received from
				         the peer.  This value is initialized to 64, and is invalid if
				         the wwpOamPeerStatus is inactive.

				         An Information OAMPDU is indicated by a valid frame with (1)
				         destination MAC address equal to that of the reserved MAC
				         address for Slow Protocols (See 43B of [802.3ah]), (2) a
				         lengthOrType field equal to the reserved type for Slow
				         Protocols, (3) a Slow Protocols subtype equal to that of the
				         subtype reserved for OAM, and (4) a OAM code that equals the
				         code reserved for Information OAMPDUs."
			::= { wwpOamPeerEntry 6 }


		-- 1.3.6.1.4.1.6141.2.400.1.2.2.1.7
		wwpOamPeerConfigRevision OBJECT-TYPE
			SYNTAX Unsigned32
			MAX-ACCESS read-only
			STATUS current
			DESCRIPTION
				"The configuration revision of the OAM peer as reflected in
				         the latest OAMPDU.  This attribute is changed by the peer
				         whenever it has a local configuration change for Ethernet OAM
				         this interface.  This value is initialized to all zeros
				         (0x00000000), and is invalid if the wwpOamPeerStatus is
				         inactive.

				         The configuration revision can be determined from the Revision

				         field of the Local Information TLV of the most recently
				         received Information OAMPDU with a Local Information TLV.

				         An Information OAMPDU is indicated by a valid frame with (1)
				         destination MAC address equal to that of the reserved MAC
				         address for Slow Protocols (See 43B of [802.3ah]), (2) a
				         lengthOrType field equal to the reserved type for Slow
				         Protocols, (3) a Slow Protocols subtype equal to that of the
				         subtype reserved for OAM, and (4) a OAM code that equals the
				         code reserved for Information OAMPDUs."
			::= { wwpOamPeerEntry 7 }


		-- 1.3.6.1.4.1.6141.2.400.1.2.2.1.8
		wwpOamPeerFunctionsSupported OBJECT-TYPE
			SYNTAX BITS
				{
				unidirectionalSupport(0),
				loopbackSupport(1),
				eventSupport(2),
				variableSupport(3)
				}
			MAX-ACCESS read-only
			STATUS current
			DESCRIPTION
				"The OAM functions supported on this Ethernet like interface.
				         OAM consists of separate functionality sets above the basic
				         discovery process.  This value indicates the capabilities of
				         the peer OAM entity with respect to these functions.  This
				         value is initialized so all bits are clear, and is invalid if
				         the wwpOamPeerStatus is inactive.

				         The capbilities of the OAM peer can be determined from the
				         configuration field of the Local Information TLV of the most
				         recently received Information OAMPDU with a Local Information
				         TLV.

				         An Information OAMPDU is indicated by a valid frame with (1)
				         destination MAC address equal to that of the reserved MAC
				         address for Slow Protocols (See 43B of [802.3ah]), (2) a
				         lengthOrType field equal to the reserved type for Slow
				         Protocols, (3) a Slow Protocols subtype equal to that of the
				         subtype reserved for OAM, and (4) a OAM code that equals the
				         code reserved for Information OAMPDUs. "
			::= { wwpOamPeerEntry 8 }

		-- 1.3.6.1.4.1.6141.2.400.1.2.2.1.9
		wwpOamLocalPort OBJECT-TYPE
			SYNTAX Integer32 (1..1000)
			MAX-ACCESS read-only
			STATUS current
			DESCRIPTION
				"An Ethernet port on local switch."
			::= { wwpOamPeerEntry 9 }


		-- 1.3.6.1.4.1.6141.2.400.1.2.3
		wwpOamLoopbackTable OBJECT-TYPE
			SYNTAX SEQUENCE OF WwpOamLoopbackEntry
			MAX-ACCESS not-accessible
			STATUS current
			DESCRIPTION
				"This table contains methods to control the loopback state of
				         the local link as well as indicating the status of the
				         loopback function.

				         Loopback can be used to place the remote OAM entity in a state
				         where every received frame (except OAMPDUs) are echoed back
				         over the same interface on which they were received.   In this
				         state, at the remote entity, 'normal' traffic is disabled as
				         only the looped back frames are transmitted on the interface.
				         Loopback is thus an intrusive operation that prohibits normal
				         data flow and should be used accordingly."
			::= { wwpOamObjs 3 }


		-- 1.3.6.1.4.1.6141.2.400.1.2.3.1
		wwpOamLoopbackEntry OBJECT-TYPE
			SYNTAX WwpOamLoopbackEntry
			MAX-ACCESS not-accessible
			STATUS current
			DESCRIPTION
				"An entry in the table, containing information on the loopback
				         status for a single Ethernet like interface.  There is an
				         entry in this table for every Ethernet like interface on which
				         supports OAM and loopback function within OAM (as indicated in
				         wwpOamFunctionsSupported)."
			INDEX { wwpOamLoopbackPort }
			::= { wwpOamLoopbackTable 1 }


		WwpOamLoopbackEntry ::=
			SEQUENCE {
				wwpOamLoopbackCommand
					INTEGER,
				wwpOamLoopbackStatus
					INTEGER,
				wwpOamLoopbackIgnoreRx
					INTEGER,
				wwpOamLoopbackPort
					Integer32
			 }

		-- 1.3.6.1.4.1.6141.2.400.1.2.3.1.1
		wwpOamLoopbackCommand OBJECT-TYPE
			SYNTAX INTEGER
				{
				noLoopback(1),
				startRemoteLoopback(2),
				stopRemoteLoopback(3)
				}
			MAX-ACCESS read-write
			STATUS current
			DESCRIPTION
				"This attribute initiates or terminates remote loopback with
				         an OAM peer.  Writing startRemoteLoopback(2) to this attribute
				         cause the local OAM client to send a loopback OAMPDU to the
				         OAM peer with the loopback enable flags set.  Writing
				         stopRemoteLoopback(3) to this attribute will cause the local
				         OAM client to send a loopback OAMPDU to the OAM peer with the
				         loopback enable flags cleared.  Writing noLoopback to this
				         attribute has no effect.

				         Writes to this attribute are ignored unless the OAM status of
				         this interface is 'operational' (wwpOamOperStatus).

				         The attribute always returns noLoopback on a read.  To
				         determine the loopback status, use the attribute
				         wwpOamLoopbackStatus. "
			::= { wwpOamLoopbackEntry 1 }


		-- 1.3.6.1.4.1.6141.2.400.1.2.3.1.2
		wwpOamLoopbackStatus OBJECT-TYPE
			SYNTAX INTEGER
				{
				noLoopback(1),
				initiatingLoopback(2),
				remoteLoopback(3),
				terminatingLoopback(4),
				localLoopback(5),
				unknown(6)
				}
			MAX-ACCESS read-only
			STATUS current
			DESCRIPTION
				"The loopback status of the OAM entity.  This status is
				         determined by a combination of the local parser and
				         multiplexer states, the remote parser and multiplexer states,
				         as well as by the actions of the local OAM client.  When
				         operating in normal mode with no loopback in progress, the
				         status reads noLoopback(1).

				         If the OAM client has sent an Loopback OAMPDU and is waiting
				         for a response, where the local parser and multiplexer states
				         are DISCARD (see [802.3ah, 57.2.11.1]), the status is
				         'initiatingLoopback'.  In this case, the local OAM entity has
				         yet to receive any acknowledgement that the remote OAM entity
				         has received its loopback command request.

				         If the local OAM client knows that the remote OAM entity is in
				         loopback mode (via the remote state information as described
				         in [802.3ah, 57.2.11.1, 30.3.6.1.15]), the status is remoteLoopback(3).  If the local OAM client is in the process
				         of terminating the remote loopback [802.3ah, 57.2.11.3,
				         30.3.6.1.14], with its local multiplexer and parser states in
				         DISCARD, the status is terminatingLoopback(4).  If the remote
				         OAM client has put the local OAM entity in loopback mode as
				         indicated by its local parser state, the status is
				         localLoopback(5).

				         The unknown(6) status indicates the parser and multiplexer
				         combination is unexpected.  This status may be returned if the
				         OAM loopback is in a transition state but should not persist.

				         The values of this attribute correspond to the following
				         values of the local and remote parser and multiplexer states.

				           value            LclPrsr   LclMux    RmtPrsr   RmtMux
				           noLoopback         FWD       FWD       FWD       FWD
				           initLoopback     DISCARD   DISCARD     FWD       FWD
				           rmtLoopback      DISCARD     FWD      LPBK    DISCARD
				           tmtngLoopback    DISCARD   DISCARD    LPBK    DISCARD
				           lclLoopback        LPBK    DISCARD   DISCARD     FWD
				           unknown            ***   any other combination   ***"
			::= { wwpOamLoopbackEntry 2 }


		-- 1.3.6.1.4.1.6141.2.400.1.2.3.1.3
		wwpOamLoopbackIgnoreRx OBJECT-TYPE
			SYNTAX INTEGER
				{
				ignore(1),
				process(2)
				}
			MAX-ACCESS read-write
			STATUS current
			DESCRIPTION
				"Since OAM loopback is a distruptive operation (user traffic
				         does not pass), this attribute provides a mechanism to provide
				         controls over whether received OAM loopback commands are
				         processed or ignored.  When the value is ignore(1), received
				         loopback commands are ignored.  When the value is process(2),
				         OAM loopback commands are processed.  The default value is to
				         ignore loopback commands (ignore(1)).

				         The attribute has no meaning if the local OAM entity does not
				         support the loopback function (as defined in
				         wwpOamFunctionsSupported). "
			::= { wwpOamLoopbackEntry 3 }


		-- 1.3.6.1.4.1.6141.2.400.1.2.3.1.4
		wwpOamLoopbackPort OBJECT-TYPE
			SYNTAX Integer32 (1..1000)
			MAX-ACCESS read-only
			STATUS current
			DESCRIPTION
				"An Ethernet port on the switch"
			::= { wwpOamLoopbackEntry 4 }


		-- 1.3.6.1.4.1.6141.2.400.1.2.4
		wwpOamStatsTable OBJECT-TYPE
			SYNTAX SEQUENCE OF WwpOamStatsEntry
			MAX-ACCESS not-accessible
			STATUS current
			DESCRIPTION
				"Statistics for the OAM function on a particular Ethernet like
				         interface."
			::= { wwpOamObjs 4 }


		-- 1.3.6.1.4.1.6141.2.400.1.2.4.1
		wwpOamStatsEntry OBJECT-TYPE
			SYNTAX WwpOamStatsEntry
			MAX-ACCESS not-accessible
			STATUS current
			DESCRIPTION
				"An entry in the table, containing statistics information on
				         the Ethernet OAM function for a single Ethernet like
				         interface."
			INDEX { wwpOamStatsPort }
			::= { wwpOamStatsTable 1 }


		WwpOamStatsEntry ::=
			SEQUENCE {
				wwpOamInformationTx
					Counter32,
				wwpOamInformationRx
					Counter32,
				wwpOamUniqueEventNotificationTx
					Counter32,
				wwpOamUniqueEventNotificationRx
					Counter32,
				wwpOamLoopbackControlTx
					Counter32,
				wwpOamLoopbackControlRx
					Counter32,
				wwpOamVariableRequestTx
					Counter32,
				wwpOamVariableRequestRx
					Counter32,
				wwpOamVariableResponseTx
					Counter32,
				wwpOamVariableResponseRx
					Counter32,
				wwpOamOrgSpecificTx
					Counter32,
				wwpOamOrgSpecificRx
					Counter32,
				wwpOamUnsupportedCodesTx
					Counter32,
				wwpOamUnsupportedCodesRx
					Counter32,
				wwpOamframesLostDueToOam
					Counter32,
				wwpOamStatsPort
					Integer32,
				wwpOamDuplicateEventNotificationTx
					Counter32,
				wwpOamDuplicateEventNotificationRx
					Counter32
			 }

		-- 1.3.6.1.4.1.6141.2.400.1.2.4.1.1
		wwpOamInformationTx OBJECT-TYPE
			SYNTAX Counter32
			UNITS "frames"
			MAX-ACCESS read-only
			STATUS current
			DESCRIPTION
				"A count of the number of Information OAMPDUs transmitted on
				         this interface.

				         An Information OAMPDU is indicated by a valid frame with (1)
				         destination MAC address equal to that of the reserved MAC
				         address for Slow Protocols (See 43B of [802.3ah]), (2) a
				         lengthOrType field equal to the reserved type for Slow
				         Protocols, (3) a Slow Protocols subtype equal to that of the
				         subtype reserved for OAM, and (4) an OAMPDU code equals the
				         OAM Information code.

				         Discontinuities of this counter can occur at re-initialization
				         of the management system, and at other times as indicated by
				         the value of the ifCounterDiscontinuityTime."
			::= { wwpOamStatsEntry 1 }


		-- 1.3.6.1.4.1.6141.2.400.1.2.4.1.2
		wwpOamInformationRx OBJECT-TYPE
			SYNTAX Counter32
			UNITS "frames"
			MAX-ACCESS read-only
			STATUS current
			DESCRIPTION
				"A count of the number of Information OAMPDUs received on this
				         interface.

				         An Information OAMPDU is indicated by a valid frame with (1)
				         destination MAC address equal to that of the reserved MAC
				         address for Slow Protocols (See 43B of [802.3ah]), (2) a
				         lengthOrType field equal to the reserved type for Slow
				         Protocols, (3) a Slow Protocols subtype equal to that of the
				         subtype reserved for OAM, and (4) an OAMPDU code equals the
				         OAM Information code.

				         Discontinuities of this counter can occur at re-initialization
				         of the management system, and at other times as indicated by
				         the value of the ifCounterDiscontinuityTime. "
			::= { wwpOamStatsEntry 2 }


		-- 1.3.6.1.4.1.6141.2.400.1.2.4.1.3
		wwpOamUniqueEventNotificationTx OBJECT-TYPE
			SYNTAX Counter32
			UNITS "frames"
			MAX-ACCESS read-only
			STATUS current
			DESCRIPTION
				"A count of the number of unique Event OAMPDUs transmitted on
				         this interface.  Event notifications may be sent in duplicate
				         to increase the probability of successfully being received,
				         given the possiblity that a frame may be lost in transit.

				         An Event Notification OAMPDU is indicated by a valid frame
				         with (1) destination MAC address equal to that of the reserved
				         MAC address for Slow Protocols (See 43B of [802.3ah]), (2) a
				         lengthOrType field equal to the reserved type for Slow
				         Protocols, (3) a Slow Protocols subtype equal to that of the
				         subtype reserved for OAM, and (4) an OAMPDU code equals the
				         OAM Event code.

				         A unique Event Notification OAMPDU is indicated as an Event
				         Notification OAMPDU with a Sequence Number field that is
				         distinct from the previously transmitted Event Notification
				         OAMPDU Sequence Number.

				         Discontinuities of this counter can occur at re-initialization
				         of the management system, and at other times as indicated by
				         the value of the ifCounterDiscontinuityTime."
			::= { wwpOamStatsEntry 3 }


		-- 1.3.6.1.4.1.6141.2.400.1.2.4.1.4
		wwpOamUniqueEventNotificationRx OBJECT-TYPE
			SYNTAX Counter32
			UNITS "frames"
			MAX-ACCESS read-only
			STATUS current
			DESCRIPTION
				"A count of the number of unique Event OAMPDUs received on
				         this interface.  Event notification OAMPDUs may be sent in
				         duplicate to increase the probability of successfully being
				         received, given the possiblity that a frame may be lost in
				         transit.

				         An Event Notification OAMPDU is indicated by a valid frame
				         with (1) destination MAC address equal to that of the reserved
				         MAC address for Slow Protocols (See 43B of [802.3ah]), (2) a
				         lengthOrType field equal to the reserved type for Slow
				         Protocols, (3) a Slow Protocols subtype equal to that of the
				         subtype reserved for OAM, and (4) an OAMPDU code equals the
				         OAM Event code.

				         A unique Event Notification OAMPDU is indicated as an Event
				         Notification OAMPDU with a Sequence Number field that is
				         distinct from the previously received Event Notification



				         OAMPDU Sequence Number.

				         Discontinuities of this counter can occur at re-initialization
				         of the management system, and at other times as indicated by
				         the value of the ifCounterDiscontinuityTime."
			::= { wwpOamStatsEntry 4 }


		-- 1.3.6.1.4.1.6141.2.400.1.2.4.1.5
		wwpOamLoopbackControlTx OBJECT-TYPE
			SYNTAX Counter32
			UNITS "frames"
			MAX-ACCESS read-only
			STATUS current
			DESCRIPTION
				"A count of the number of Loopback Control OAMPDUs transmitted
				         on this interface.

				         An Loopback Conrol OAMPDU is indicated by a valid frame with
				         (1) destination MAC address equal to that of the reserved MAC
				         address for Slow Protocols (See 43B of [802.3ah]), (2) a
				         lengthOrType field equal to the reserved type for Slow
				         Protocols, (3) a Slow Protocols subtype equal to that of the
				         subtype reserved for OAM, and (4) an OAMPDU code equals the
				         OAM Loopback Control code.

				         Discontinuities of this counter can occur at re-initialization
				         of the management system, and at other times as indicated by
				         the value of the ifCounterDiscontinuityTime.  "
				       REFERENCE   "[802.3ah], 30.3.6.1.26."
			::= { wwpOamStatsEntry 5 }


		-- 1.3.6.1.4.1.6141.2.400.1.2.4.1.6
		wwpOamLoopbackControlRx OBJECT-TYPE
			SYNTAX Counter32
			UNITS "frames"
			MAX-ACCESS read-only
			STATUS current
			DESCRIPTION
				"A count of the number of Loopback Control OAMPDUs transmitted
				         on this interface.

				         An Loopback Control OAMPDU is indicated by a valid frame with
				         (1) destination MAC address equal to that of the reserved MAC
				         address for Slow Protocols (See 43B of [802.3ah]), (2) a
				         lengthOrType field equal to the reserved type for Slow
				         Protocols, (3) a Slow Protocols subtype equal to that of the
				         subtype reserved for OAM, and (4) an OAMPDU code equals the
				         OAM Loopback Control code.

				         Discontinuities of this counter can occur at re-initialization
				         of the management system, and at other times as indicated by
				         the value of the ifCounterDiscontinuityTime.  "
				       REFERENCE   "[802.3ah], 30.3.6.1.27."
			::= { wwpOamStatsEntry 6 }


		-- 1.3.6.1.4.1.6141.2.400.1.2.4.1.7
		wwpOamVariableRequestTx OBJECT-TYPE
			SYNTAX Counter32
			UNITS "frames"
			MAX-ACCESS read-only
			STATUS current
			DESCRIPTION
				"A count of the number of Variable Request OAMPDUs transmitted
				         on this interface.

				         An Variable Request OAMPDU is indicated by a valid frame with
				         (1) destination MAC address equal to that of the reserved MAC
				         address for Slow Protocols (See 43B of [802.3ah]), (2) a
				         lengthOrType field equal to the reserved type for Slow
				         Protocols, (3) a Slow Protocols subtype equal to that of the
				         subtype reserved for OAM, and (4) an OAMPDU code equals the
				         OAM Variable Request code.

				         Discontinuities of this counter can occur at re-initialization
				         of the management system, and at other times as indicated by
				         the value of the ifCounterDiscontinuityTime.  "
				       REFERENCE   "[802.3ah], 30.3.6.1.28."
			::= { wwpOamStatsEntry 7 }


		-- 1.3.6.1.4.1.6141.2.400.1.2.4.1.8
		wwpOamVariableRequestRx OBJECT-TYPE
			SYNTAX Counter32
			UNITS "frames"
			MAX-ACCESS read-only
			STATUS current
			DESCRIPTION
				"A count of the number of Variable Request OAMPDUs received on
				         this interface.




				         An Variable Request OAMPDU is indicated by a valid frame with
				         (1) destination MAC address equal to that of the reserved MAC
				         address for Slow Protocols (See 43B of [802.3ah]), (2) a
				         lengthOrType field equal to the reserved type for Slow
				         Protocols, (3) a Slow Protocols subtype equal to that of the
				         subtype reserved for OAM, and (4) an OAMPDU code equals the
				         OAM Variable Request code.

				         Discontinuities of this counter can occur at re-initialization
				         of the management system, and at other times as indicated by
				         the value of the ifCounterDiscontinuityTime."
			::= { wwpOamStatsEntry 8 }


		-- 1.3.6.1.4.1.6141.2.400.1.2.4.1.9
		wwpOamVariableResponseTx OBJECT-TYPE
			SYNTAX Counter32
			UNITS "frames"
			MAX-ACCESS read-only
			STATUS current
			DESCRIPTION
				"A count of the number of Variable Response OAMPDUs
				         transmitted on this interface.

				         An Variable Response OAMPDU is indicated by a valid frame with
				         (1) destination MAC address equal to that of the reserved MAC
				         address for Slow Protocols (See 43B of [802.3ah]), (2) a
				         lengthOrType field equal to the reserved type for Slow
				         Protocols, (3) a Slow Protocols subtype equal to that of the
				         subtype reserved for OAM, and (4) an OAMPDU code equals the
				         OAM Variable Response code.

				         Discontinuities of this counter can occur at re-initialization
				         of the management system, and at other times as indicated by
				         the value of the ifCounterDiscontinuityTime. "
			::= { wwpOamStatsEntry 9 }


		-- 1.3.6.1.4.1.6141.2.400.1.2.4.1.10
		wwpOamVariableResponseRx OBJECT-TYPE
			SYNTAX Counter32
			UNITS "frames"
			MAX-ACCESS read-only
			STATUS current
			DESCRIPTION
				"A count of the number of Variable Response OAMPDUs received
				         on this interface.

				         An Variable Response OAMPDU is indicated by a valid frame with
				         (1) destination MAC address equal to that of the reserved MAC



				         address for Slow Protocols (See 43B of [802.3ah]), (2) a
				         lengthOrType field equal to the reserved type for Slow
				         Protocols, (3) a Slow Protocols subtype equal to that of the
				         subtype reserved for OAM, and (4) an OAMPDU code equals the
				         OAM Variable Response code.

				         Discontinuities of this counter can occur at re-initialization
				         of the management system, and at other times as indicated by
				         the value of the ifCounterDiscontinuityTime. "
			::= { wwpOamStatsEntry 10 }


		-- 1.3.6.1.4.1.6141.2.400.1.2.4.1.11
		wwpOamOrgSpecificTx OBJECT-TYPE
			SYNTAX Counter32
			UNITS "frames"
			MAX-ACCESS read-only
			STATUS current
			DESCRIPTION
				"A count of the number of Organization Specific OAMPDUs
				         transmitted on this interface.

				         An Organization Specific OAMPDU is indicated by a valid frame
				         with (1) destination MAC address equal to that of the reserved
				         MAC address for Slow Protocols (See 43B of [802.3ah]), (2) a
				         lengthOrType field equal to the reserved type for Slow
				         Protocols, (3) a Slow Protocols subtype equal to that of the
				         subtype reserved for OAM, and (4) an OAMPDU code equals the
				         OAM Organization Specific code.

				         Discontinuities of this counter can occur at re-initialization
				         of the management system, and at other times as indicated by
				         the value of the ifCounterDiscontinuityTime. "
			::= { wwpOamStatsEntry 11 }


		-- 1.3.6.1.4.1.6141.2.400.1.2.4.1.12
		wwpOamOrgSpecificRx OBJECT-TYPE
			SYNTAX Counter32
			UNITS "frames"
			MAX-ACCESS read-only
			STATUS current
			DESCRIPTION
				"A count of the number of Organization Specific OAMPDUs
				         received on this interface.

				         An Organization Specific OAMPDU is indicated by a valid frame
				         with (1) destination MAC address equal to that of the reserved
				         MAC address for Slow Protocols (See 43B of [802.3ah]), (2) a
				         lengthOrType field equal to the reserved type for Slow



				         Protocols, (3) a Slow Protocols subtype equal to that of the
				         subtype reserved for OAM, and (4) an OAMPDU code equals the
				         OAM Organization Specific code.

				         Discontinuities of this counter can occur at re-initialization
				         of the management system, and at other times as indicated by
				         the value of the ifCounterDiscontinuityTime. "
			::= { wwpOamStatsEntry 12 }


		-- 1.3.6.1.4.1.6141.2.400.1.2.4.1.13
		wwpOamUnsupportedCodesTx OBJECT-TYPE
			SYNTAX Counter32
			UNITS "frames"
			MAX-ACCESS read-only
			STATUS current
			DESCRIPTION
				"A count of the number of OAMPDUs transmitted on this
				         interface with an unsupported op-code.

				         An unsupported opcode OAMPDU is indicated by a valid frame
				         with (1) destination MAC address equal to that of the reserved
				         MAC address for Slow Protocols (See 43B of [802.3ah]), (2) a
				         lengthOrType field equal to the reserved type for Slow
				         Protocols, (3) a Slow Protocols subtype equal to that of the
				         subtype reserved for OAM, and (4) an OAMPDU code equals the
				         opcode for a function that is not supported by the device.

				         Discontinuities of this counter can occur at re-initialization
				         of the management system, and at other times as indicated by
				         the value of the ifCounterDiscontinuityTime. "
			::= { wwpOamStatsEntry 13 }


		-- 1.3.6.1.4.1.6141.2.400.1.2.4.1.14
		wwpOamUnsupportedCodesRx OBJECT-TYPE
			SYNTAX Counter32
			UNITS "frames"
			MAX-ACCESS read-only
			STATUS current
			DESCRIPTION
				"A count of the number of OAMPDUs received on this interface
				         with an unsupported op-code.

				         An unsupported opcode OAMPDU is indicated by a valid frame
				         with (1) destination MAC address equal to that of the reserved
				         MAC address for Slow Protocols (See 43B of [802.3ah]), (2) a
				         lengthOrType field equal to the reserved type for Slow
				         Protocols, (3) a Slow Protocols subtype equal to that of the
				         subtype reserved for OAM, and (4) an OAMPDU code equals the
				         opcode for a function that is not supported by the device.




				         Discontinuities of this counter can occur at re-initialization
				         of the management system, and at other times as indicated by
				         the value of the ifCounterDiscontinuityTime."
			::= { wwpOamStatsEntry 14 }


		-- 1.3.6.1.4.1.6141.2.400.1.2.4.1.15
		wwpOamframesLostDueToOam OBJECT-TYPE
			SYNTAX Counter32
			UNITS "frames"
			MAX-ACCESS read-only
			STATUS current
			DESCRIPTION
				"A count of the number of frames that were dropped by the OAM
				         multiplexer.  Since the OAM mulitplexer has multiple inputs
				         and a single output, there may be cases where frames are
				         dropped due to transmit resource contention.  This counter is
				         incremented whenever a frame is dropped by the OAM layer.
				         When this counter is incremented, no other counters in this
				         MIB are incremented.

				         Discontinuities of this counter can occur at re-initialization
				         of the management system, and at other times as indicated by
				         the value of the ifCounterDiscontinuityTime."
			::= { wwpOamStatsEntry 15 }


		-- 1.3.6.1.4.1.6141.2.400.1.2.4.1.16
		wwpOamStatsPort OBJECT-TYPE
			SYNTAX Integer32 (1..1000)
			MAX-ACCESS read-only
			STATUS current
			DESCRIPTION
				"An Ethernet port on the switch"
			::= { wwpOamStatsEntry 16 }


		-- 1.3.6.1.4.1.6141.2.400.1.2.4.1.17
		wwpOamDuplicateEventNotificationTx OBJECT-TYPE
			SYNTAX Counter32
			UNITS "frames"
			MAX-ACCESS read-only
			STATUS current
			DESCRIPTION
				"A count of the number of duplicate Event OAMPDUs transmitted
				         on this interface.  Event notification OAMPDUs may be sent in
				         duplicate to increase the probability of successfully being
				         received, given the possiblity that a frame may be lost in
				         transit.

				         An Event Notification OAMPDU is indicated by a valid frame
				         with (1) destination MAC address equal to that of the reserved
				         MAC address for Slow Protocols (See 43B of [802.3ah]), (2) a
				         lengthOrType field equal to the reserved type for Slow
				         Protocols, (3) a Slow Protocols subtype equal to that of the
				         subtype reserved for OAM, and (4) an OAMPDU code equals the
				         OAM Event code.

				         A duplicate Event Notification OAMPDU is indicated as an Event
				         Notification OAMPDU with a Sequence Number field that is
				         identical to the previously transmitted Event Notification
				         OAMPDU Sequence Number.

				         Discontinuities of this counter can occur at re-initialization
				         of the management system, and at other times as indicated by
				         the value of the ifCounterDiscontinuityTime."
			::= { wwpOamStatsEntry 17 }


		-- 1.3.6.1.4.1.6141.2.400.1.2.4.1.18
		wwpOamDuplicateEventNotificationRx OBJECT-TYPE
			SYNTAX Counter32
			UNITS "frames"
			MAX-ACCESS read-only
			STATUS current
			DESCRIPTION
				"A count of the number of duplicate Event OAMPDUs received on
				         this interface.  Event notification OAMPDUs may be sent in
				         duplicate to increase the probability of successfully being
				         received, given the possiblity that a frame may be lost in
				         transit.

				         An Event Notification OAMPDU is indicated by a valid frame
				         with (1) destination MAC address equal to that of the reserved
				         MAC address for Slow Protocols (See 43B of [802.3ah]), (2) a
				         lengthOrType field equal to the reserved type for Slow
				         Protocols, (3) a Slow Protocols subtype equal to that of the
				         subtype reserved for OAM, and (4) an OAMPDU code equals the
				         OAM Event code.

				         A duplicate Event Notification OAMPDU is indicated as an Event
				         Notification OAMPDU with a Sequence Number field that is
				         identical to the previously received Event Notification OAMPDU
				         Sequence Number.

				         Discontinuities of this counter can occur at re-initialization
				         of the management system, and at other times as indicated by
				         the value of the ifCounterDiscontinuityTime. "
			::= { wwpOamStatsEntry 18 }

     -- 1.3.6.1.4.1.6141.2.400.1.2.5
		wwpOamSystemEnableDisable OBJECT-TYPE
			SYNTAX INTEGER
				{
				enable(1),
				disable(2)
				}
			MAX-ACCESS read-write
			STATUS current
			DESCRIPTION
				"Global Enable/disable OAM on the switch"
			::= { wwpOamObjs 5 }

     -- 1.3.6.1.4.1.6141.2.400.1.2.6

     wwpOamEventConfigTable OBJECT-TYPE
       SYNTAX     SEQUENCE OF WwpOamEventConfigEntry
       MAX-ACCESS not-accessible
       STATUS     current
       DESCRIPTION
         "Ethernet OAM includes the ability to generate and receive
         event notifications to indicate various link problems.  This
         table contains the mechanisms to configure the thresholds to
         generate the standard Ethernet OAM events.

         These events are:
           - Errored Symbol Period Event.  Generated when the number of
             symbol errors exceeds a threshold within a given window
             defined by a number of symbols (e.g. 1,000 symbols out of
             1,000,000 had errors).

           - Errored Frame Period Event.  Generated when the number of
             frame errors exceeds a threshold within a given window
             defined by a number of frames (e.g. 10 frames out of 1000
             had errors).
           - Errored Frame Event.  Generated when the number of frame
             errors exceeds a threshold within a given window defined
             by a period of time (e.g. 10 frames in 1 second had
             errors).
           - Errored Frame Seconds Summary Event.  Generated when the
             number of errored frame seconds exceeds a threshold within
             a given time period (e.g. 10 errored frame seconds within
             the last 100 seconds).  An errored frame second is defined
             as a 1 second interval which had >0 frame errors.
         "
       ::= { wwpOamObjs 6 }

     -- 1.3.6.1.4.1.6141.2.400.1.2.6.1
     wwpOamEventConfigEntry OBJECT-TYPE
       SYNTAX      WwpOamEventConfigEntry
       MAX-ACCESS  not-accessible
       STATUS      current
       DESCRIPTION
         "Event configuration information is available for every
         Ethernet like interface that supports OAM and the event
         function of OAM as indicated in the wwpOamFunctionsSupported
         attribute.

         Event configuration controls when the local management entity
         sends Event Notification OAMPDUs to its OAM peer.  "
       INDEX       { wwpOamEventPort }
       ::= { wwpOamEventConfigTable 1 }

     WwpOamEventConfigEntry ::=
       SEQUENCE {
       			 wwpOamEventPort				   Integer32,
                 wwpOamErrFramePeriodWindow        Unsigned32,
                 wwpOamErrFramePeriodThreshold     Unsigned32,
                 wwpOamErrFramePeriodEvNotifEnable INTEGER,
                 wwpOamErrFrameWindow              Unsigned32,
                 wwpOamErrFrameThreshold           Unsigned32,
                 wwpOamErrFrameEvNotifEnable       INTEGER,
                 wwpOamErrFrameSecsSummaryWindow   Integer32,
                 wwpOamErrFrameSecsSummaryThreshold Integer32,
                 wwpOamErrFrameSecsEvNotifEnable   INTEGER,
           		 wwpOamDyingGaspEnable              INTEGER,
           		 wwpOamCriticalEventEnable          INTEGER
               }

  	-- 1.3.6.1.4.1.6141.2.400.1.2.6.1.1
	wwpOamEventPort OBJECT-TYPE
		SYNTAX Integer32 (1..1000)
		MAX-ACCESS read-only
		STATUS current
		DESCRIPTION
		"An Ethernet port on the switch"
		::= { wwpOamEventConfigEntry 1 }

     -- 1.3.6.1.4.1.6141.2.400.1.2.6.1.2
     wwpOamErrFramePeriodWindow OBJECT-TYPE
       SYNTAX      Unsigned32
       UNITS       "frames"
       MAX-ACCESS  read-write
       STATUS      current
       DESCRIPTION
         "The number of frames over which the threshold is defined.
  		 The default value of the window is the number of minimum size
         Ethernet frames that can be received over the physical layer
         in one second.

         If wwpOamErrFramePeriodThreshold frame errors occur within a
         window of wwpOamErrFramePeriodWindow frames, an Event
         Notification OAMPDU should be generated with an Errored Frame
         Period Event TLV indicating the threshold has been crossed in
         this window.  "
       REFERENCE   "[802.3ah], 30.3.6.1.38"
       ::= { wwpOamEventConfigEntry 2 }

     -- 1.3.6.1.4.1.6141.2.400.1.2.6.1.3
     wwpOamErrFramePeriodThreshold OBJECT-TYPE
       SYNTAX      Unsigned32
       UNITS       "frames"
       MAX-ACCESS  read-write
       STATUS      current
       DESCRIPTION
         "The number of frame errors that must occur for this event to
         be triggered.  The default value is one frame error.

         If wwpOamErrFramePeriodThreshold frame errors occur within a
         window of wwpOamErrFramePeriodWindow frames, an Event
         Notification OAMPDU should be generated with an Errored Frame
         Period Event TLV indicating the threshold has been crossed in
         this window.  "
       REFERENCE   "[802.3ah], 30.3.6.1.38"
       ::= { wwpOamEventConfigEntry 3 }

     -- 1.3.6.1.4.1.6141.2.400.1.2.6.1.4
     wwpOamErrFramePeriodEvNotifEnable OBJECT-TYPE
       SYNTAX      INTEGER { enabled(1), disabled(2) }
       MAX-ACCESS  read-write
       STATUS      current
       DESCRIPTION
         "Indicates whether the occurence of an Errored Frame Period
         Event should result in an Event Notification OAMPDU generated
         by the OAM layer.

         By default, this object should have the value disabled(2) for
         Ethernet like interfaces that support OAM.  If the OAM layer
         does not support event notifications (as indicated via the
         wwpOamFunctionsSupported attribute), this value is ignored. "
       ::= { wwpOamEventConfigEntry 4 }

     -- 1.3.6.1.4.1.6141.2.400.1.2.6.1.5
     wwpOamErrFrameWindow OBJECT-TYPE
       SYNTAX      Unsigned32
       UNITS       "tenths of a second"
       MAX-ACCESS  read-write
       STATUS      current
       DESCRIPTION
         "The amount of time (in 100ms increments) over which the
         threshold is defined.  The default value is 10 (1 second).

        If wwpOamErrFrameThreshold frame errors occur within a window
        of wwpOamErrFrameWindow seconds (measured in tenths of
        seconds), an Event Notification OAMPDU should be generated with
        an Errored Frame Event TLV indicating the threshold has been
        crossed in this window.  "
       REFERENCE   "[802.3ah], 30.3.6.1.36"
       ::= { wwpOamEventConfigEntry 5 }

     -- 1.3.6.1.4.1.6141.2.400.1.2.6.1.6
     wwpOamErrFrameThreshold OBJECT-TYPE
       SYNTAX      Unsigned32
       UNITS       "frames"
       MAX-ACCESS  read-write
       STATUS      current
       DESCRIPTION
         "The number of frame errors that must occur for this event to
         be triggered.  The default value is one frame error.

         If wwpOamErrFrameThreshold frame errors occur within a window
         of wwpOamErrFrameWindow (in tenths of seconds), an Event
         Notification OAMPDU should be generated with an Errored Frame
         Event TLV indicating the threshold has been crossed in this
         window.  "
       REFERENCE   "[802.3ah], 30.3.6.1.36"
       ::= { wwpOamEventConfigEntry 6 }

     -- 1.3.6.1.4.1.6141.2.400.1.2.6.1.7
     wwpOamErrFrameEvNotifEnable OBJECT-TYPE
       SYNTAX      INTEGER { enabled(1), disabled(2) }
       MAX-ACCESS  read-write
       STATUS      current
       DESCRIPTION
         "Indicates whether the occurence of an Errored Frame Event
         should result in an Event Notification OAMPDU generated by the
         OAM layer.

         By default, this object should have the value disabled(2) for
         Ethernet like interfaces that support OAM.  If the OAM layer
         does not support event notifications (as indicated via the
         wwpOamFunctionsSupported attribute), this value is ignored. "
       ::= { wwpOamEventConfigEntry 7 }

     -- 1.3.6.1.4.1.6141.2.400.1.2.6.1.8
     wwpOamErrFrameSecsSummaryWindow OBJECT-TYPE
       SYNTAX      Integer32 (100..9000)
       UNITS       "tenths of a second"
       MAX-ACCESS  read-write
       STATUS      current
       DESCRIPTION
         "The amount of time (in 100ms intervals) over which the
         threshold is defined.  The default value is 600 (60 seconds).

         If wwpOamErrFrameSecsSummaryThreshold frame errors occur
         within a window of wwpOamErrFrameSecsSummaryWindow (in tenths
         of seconds), an Event Notification OAMPDU should be generated
         with an Errored Frame Seconds Summary Event TLV indicating the
         threshold has been crossed in this window.  "
       REFERENCE   "[802.3ah], 30.3.6.1.40"
       ::= { wwpOamEventConfigEntry 8 }

     -- 1.3.6.1.4.1.6141.2.400.1.2.6.1.9
     wwpOamErrFrameSecsSummaryThreshold OBJECT-TYPE
       SYNTAX      Integer32
       UNITS       "errored frame seconds"
       MAX-ACCESS  read-write
       STATUS      current
       DESCRIPTION
         "The number of errored frame seconds that must occur for this
         event to be triggered.  The default value is one errored frame
         second.

         If wwpOamErrFrameSecsSummaryThreshold frame errors occur
         within a window of wwpOamErrFrameSecsSummaryWindow (in tenths
         of seconds), an Event Notification OAMPDU should be generated
         with an Errored Frame Seconds Summary Event TLV indicating the
         threshold has been crossed in this window.  "
       REFERENCE   "[802.3ah], 30.3.6.1.40"
       ::= { wwpOamEventConfigEntry 9 }

     -- 1.3.6.1.4.1.6141.2.400.1.2.6.1.10
     wwpOamErrFrameSecsEvNotifEnable OBJECT-TYPE
       SYNTAX      INTEGER { enabled(1), disabled(2) }
       MAX-ACCESS  read-write
       STATUS      current
       DESCRIPTION
         "Indicates whether the occurence of an Errored Frame Seconds
         Summary Event should result in an Event Notification OAMPDU
         generated by the OAM layer.

         By default, this object should have the value disabled(2) for
         Ethernet like interfaces that support OAM.  If the OAM layer
         does not support event notifications (as indicated via the
         wwpOamFunctionsSupported attribute), this value is ignored."
       ::= { wwpOamEventConfigEntry 10 }

     -- 1.3.6.1.4.1.6141.2.400.1.2.6.1.11
     wwpOamDyingGaspEnable OBJECT-TYPE
       SYNTAX      INTEGER { enabled(1), disabled(2) }
       MAX-ACCESS  read-write
       STATUS      current
       DESCRIPTION
         "Indicates whether the local device should attempt to indicate
         a dying gasp fault via the OAMPDU flags field to its peer OAM
         entity.  If the system does not support dying gasp capability,
         setting this object has no effect, and reading the object
         should always result in 'disabled(2)'.

         By default, this object should have the value disabled(2) for
         Ethernet like interfaces that support OAM.  If the OAM layer
         does not support event notifications (as indicated via the
         wwpOamFunctionsSupported attribute), this value is ignored."
       ::= { wwpOamEventConfigEntry 11 }

     -- 1.3.6.1.4.1.6141.2.400.1.2.6.1.12
     wwpOamCriticalEventEnable OBJECT-TYPE
       SYNTAX      INTEGER { enabled(1), disabled(2) }
       MAX-ACCESS  read-write
       STATUS      current
       DESCRIPTION
         "Indicates whether the local device should attempt to indicate
         a critical event fault via the OAMPDU flags field to its peer
         OAM entity.  If the system does not support critical event
         capability, setting this object has no effect, and reading the
         object should always result in 'disabled(2)'.

         By default, this object should have the value disabled(2) for
         Ethernet like interfaces that support OAM.  If the OAM layer
         does not support event notifications (as indicated via the
         wwpOamFunctionsSupported attribute), this value is ignored."
       ::= { wwpOamEventConfigEntry 12 }


	-- 1.3.6.1.4.1.6141.2.400.1.2.7

     wwpOamEventLogTable   OBJECT-TYPE
       SYNTAX       SEQUENCE OF WwpOamEventLogEntry
       MAX-ACCESS   not-accessible
       STATUS       current
       DESCRIPTION
         "This table records a history of the events that have occurred
         at the Ethernet OAM level.  These events can include locally
         detected events, which may result in locally generated
         OAMPDUs, and remotely detected events, which are detected by
         the OAM peer entity and signaled to the local entity via
         Ethernet OAM.  Ethernet OAM events can be signaled by Event
         Notification OAMPDUs or by the flags field in any OAMPDU.  "
         ::= { wwpOamObjs 7 }

     -- 1.3.6.1.4.1.6141.2.400.1.2.7.1
     wwpOamEventLogEntry OBJECT-TYPE
       SYNTAX      WwpOamEventLogEntry
       MAX-ACCESS  not-accessible
       STATUS      current
       DESCRIPTION "An entry in the wwpOamEventLogTable."
       INDEX       { wwpOamEventLogPort, wwpOamEventLogIndex }
       ::= { wwpOamEventLogTable 1 }

     WwpOamEventLogEntry ::=
       SEQUENCE {
         wwpOamEventLogPort                 Integer32,
         wwpOamEventLogIndex                Unsigned32,
         wwpOamEventLogTimestamp            TimeStamp,
         wwpOamEventLogOui                  OCTET STRING(SIZE(3)),
         wwpOamEventLogType                 Unsigned32,
         wwpOamEventLogLocation             INTEGER,
         wwpOamEventLogWindowHi             Unsigned32,
         wwpOamEventLogWindowLo             Unsigned32,
         wwpOamEventLogThresholdHi          Unsigned32,
         wwpOamEventLogThresholdLo          Unsigned32,
         wwpOamEventLogValue                Counter64,
         wwpOamEventLogRunningTotal         Counter64,
         wwpOamEventLogEventTotal           Unsigned32
       }

  	-- 1.3.6.1.4.1.6141.2.400.1.2.7.1.1
	wwpOamEventLogPort OBJECT-TYPE
		SYNTAX Integer32 (1..1000)
		MAX-ACCESS read-only
		STATUS current
		DESCRIPTION
		"An Ethernet port on the switch"
		::= { wwpOamEventLogEntry 1 }

     -- 1.3.6.1.4.1.6141.2.400.1.2.7.1.2
     wwpOamEventLogIndex       OBJECT-TYPE
       SYNTAX      Unsigned32
       MAX-ACCESS  read-only
       STATUS      current
       DESCRIPTION
         "An arbitrary integer for identifiying individual events
         within the event log.  "
       ::= { wwpOamEventLogEntry 2 }

     -- 1.3.6.1.4.1.6141.2.400.1.2.7.1.3
     wwpOamEventLogTimestamp  OBJECT-TYPE
       SYNTAX      TimeStamp
       MAX-ACCESS  read-only
       STATUS      current
       DESCRIPTION
         "The value of sysUpTime at the time of the logged event.  For
         locally generated events, the time of the event can be
         accurately retrieved from sysUpTime.  For remotely generated
         events, the time of the event is indicated by the reception of
         the Event Notification OAMPDU indicating the event occurred on
         the peer.  A system may attempt to adjust the timestamp value
         to more accurately reflect the time of the event at the peer
         OAM entity by using other information, such as that found in
         the timestamp found of the Event Notification TLVs, which
         provides an indication of the relative time between events at
         the peer entity.  "
       ::= { wwpOamEventLogEntry 3 }

     -- 1.3.6.1.4.1.6141.2.400.1.2.7.1.4
     wwpOamEventLogOui  OBJECT-TYPE
       SYNTAX      OCTET STRING(SIZE(3))
       MAX-ACCESS  read-only
       STATUS      current
       DESCRIPTION
         "The OUI of the entity defining the object type.  All IEEE
         802.3 defined events (as appearing in [802.3ah] except for the
         Organizationally Unique Event TLVs) use the IEEE 802.3 OUI of
         0x0180C2.  Organizations defining their own Event Notification
         TLVs include their OUI in the Event Notification TLV which
         gets reflected here.  "
       ::= { wwpOamEventLogEntry 4 }

     -- 1.3.6.1.4.1.6141.2.400.1.2.7.1.5
     wwpOamEventLogType      OBJECT-TYPE
       SYNTAX      Unsigned32
       MAX-ACCESS  read-only
       STATUS      current
       DESCRIPTION
         "The type of event that generated this entry in the event log.

         When the OUI is the IEEE 802.3 OUI of 0x0180C2, the following
         event types are defined:
             erroredSymbolEvent(1),
             erroredFramePeriodEvent (2),
             erroredFrameEvent(3),
             erroredFrameSecondsEvent(4),
             linkFault(256),
             dyingGaspEvent(257),
             criticalLinkEvent(258)
         The first four are considered threshold crossing events as
         they are generated when a metric exceeds a given value within
         a specified window.  The other three are not threshold
         crossing events.

         When the OUI is not 0x0180C2, then some other organization has
         defined the event space.  If event subtyping is known to the
         implementation, it may be reflected here.  Otherwise, this
         value should return all Fs (0xFFFFFFFF).
         "
       REFERENCE   "[802.3ah], 30.3.6.1.10 and 57.5.3."
       ::= { wwpOamEventLogEntry 5 }

     -- 1.3.6.1.4.1.6141.2.400.1.2.7.1.6
     wwpOamEventLogLocation OBJECT-TYPE
       SYNTAX      INTEGER { local(1), remote(2) }
       MAX-ACCESS  read-only
       STATUS      current
       DESCRIPTION
         "Whether this event occurred locally, or was received from the
         OAM peer via Ethernet OAM."
       ::= { wwpOamEventLogEntry 6 }

     -- 1.3.6.1.4.1.6141.2.400.1.2.7.1.7
     wwpOamEventLogWindowHi      OBJECT-TYPE
       SYNTAX      Unsigned32
       MAX-ACCESS  read-only
       STATUS      current
       DESCRIPTION
         "If the event represents a threshold crossing event, the two
         objects wwpOamEventWindowHi and wwpOamEventWindowLo form an
         unsigned 64-bit integer yielding the window over which the
         value was measured for the threshold crossing event (e.g. 5,
         when 11 occurrences happened in 5 seconds while the threshold
         was 10).   The two objects are combined as:

         wwpOamEventLogWindow = ((2^32) * wwpOamEventLogWindowHi)
                                         + wwpOamEventLogWindowLo


         Otherwise, this value is returned as all F's (0xFFFFFFFF) and
         adds no useful information.  "
       REFERENCE   "[802.3ah], 30.3.6.1.37 and 57.5.3.2."
       ::= { wwpOamEventLogEntry 7 }

     -- 1.3.6.1.4.1.6141.2.400.1.2.7.1.8
     wwpOamEventLogWindowLo      OBJECT-TYPE
       SYNTAX      Unsigned32
       MAX-ACCESS  read-only
       STATUS      current
       DESCRIPTION
         "If the event represents a threshold crossing event, the two
         objects wwpOamEventWindowHi and wwpOamEventWindowLo form an
         unsigned 64-bit integer yielding the window over which the
         value was measured for the threshold crossing event (e.g. 5,
         when 11 occurrences happened in 5 seconds while the threshold
         was 10).   The two objects are combined as:

         wwpOamEventLogWindow = ((2^32) * wwpOamEventLogWindowHi)
                                         + wwpOamEventLogWindowLo

         Otherwise, this value is returned as all F's (0xFFFFFFFF) and
         adds no useful information.  "
       REFERENCE   "[802.3ah], 30.3.6.1.37 and 57.5.3.2."
       ::= { wwpOamEventLogEntry 8 }

     -- 1.3.6.1.4.1.6141.2.400.1.2.7.1.9
     wwpOamEventLogThresholdHi      OBJECT-TYPE
       SYNTAX      Unsigned32
       MAX-ACCESS  read-only
       STATUS      current
       DESCRIPTION
         "If the event represents a threshold crossing event, the two
         objects wwpOamEventThresholdHi and wwpOamEventThresholdLo
         form an unsigned 64-bit integer yielding the value that was
         crossed for the threshold crossing event (e.g. 10, when 11
         occurrences happened in 5 seconds while the threshold was 10).
         The two objects are combined as:

       wwpOamEventLogThreshold = ((2^32) * wwpOamEventLogThresholdHi)
                                          + wwpOamEventLogThresholdLo

         Otherwise, this value is returned as all F's (0xFFFFFFFF) and
         adds no useful information.  "
       REFERENCE   "[802.3ah], 30.3.6.1.37 and 57.5.3.2."
       ::= { wwpOamEventLogEntry 9 }

     -- 1.3.6.1.4.1.6141.2.400.1.2.7.1.10
     wwpOamEventLogThresholdLo      OBJECT-TYPE
       SYNTAX      Unsigned32
       MAX-ACCESS  read-only
       STATUS      current
       DESCRIPTION
         "If the event represents a threshold crossing event, the two
         objects wwpOamEventThresholdHi and wwpOamEventThresholdLo
         form an unsigned 64-bit integer yielding the value that was
         crossed for the threshold crossing event (e.g. 10, when 11
         occurrences happened in 5 seconds while the threshold was 10).
         The two objects are combined as:

       wwpOamEventLogThreshold = ((2^32) * wwpOamEventLogThresholdHi)
                                          + wwpOamEventLogThresholdLo

         Otherwise, this value is returned as all F's (0xFFFFFFFF) and
         adds no useful information.  "
       REFERENCE   "[802.3ah], 30.3.6.1.37 and 57.5.3.2."
       ::= { wwpOamEventLogEntry 10 }

     -- 1.3.6.1.4.1.6141.2.400.1.2.7.1.11
     wwpOamEventLogValue      OBJECT-TYPE
       SYNTAX      Counter64
       MAX-ACCESS  read-only
       STATUS      current
       DESCRIPTION
         "If the event represents a threshold crossing event, this
         value indicates the value of the parameter within the given
         window that generated this event (e.g. 11, when 11 occurrences
         happened in 5 seconds while the threshold was 10).

         Otherwise, this value is returned as all F's
         (0xFFFFFFFFFFFFFFFF) and adds no useful information.
         "
       REFERENCE   "[802.3ah], 30.3.6.1.37 and 57.5.3.2."
       ::= { wwpOamEventLogEntry 11 }

     -- 1.3.6.1.4.1.6141.2.400.1.2.7.1.12
     wwpOamEventLogRunningTotal      OBJECT-TYPE
       SYNTAX      Counter64
       MAX-ACCESS  read-only
       STATUS      current
       DESCRIPTION
         "This value respresents the total number of times this
         occurence has happened since the last reset (e.g. 3253, when
         3253 symbol errors have occurred since the last reset, which
         has resulted in 51 symbol error threshold crossing events
         since the last reset).  "
       REFERENCE   "[802.3ah], 30.3.6.1.37 and 57.5.3.2."
       ::= { wwpOamEventLogEntry 12 }

     -- 1.3.6.1.4.1.6141.2.400.1.2.7.1.13
     wwpOamEventLogEventTotal      OBJECT-TYPE
       SYNTAX      Unsigned32
       MAX-ACCESS  read-only
       STATUS      current
       DESCRIPTION
         "This value respresents the total number of times one or ore
         of these occurences have resulted in an event (e.g. 51 when
         3253 symbol errors have occurred since the last reset, which
         has resulted in 51 symbol error threshold crossing events
         since the last reset).  "
       REFERENCE   "[802.3ah], 30.3.6.1.37 and 57.5.3.2."
       ::= { wwpOamEventLogEntry 13 }


  -- 1.3.6.1.4.1.6141.2.400.1.3
     wwpOamEvents OBJECT IDENTIFIER ::= { wwpOamMIB 3 }

  -- 1.3.6.1.4.1.6141.2.400.1.3.0
     wwpOamEventsV2 OBJECT IDENTIFIER ::= { wwpOamEvents 0 }


   END

--
-- WWP-OAM-MIB.my
--
