--
 -- WWP-PORT-STATSMIB.my
 --
 --
 -- NOTE WELL
 -- Starting from LE21X 2.0, the object wwpPortStatsReset mentioned
 -- in this MIB has been deprecated. The WWP products no longer
 -- will provide the functionlaity to reset port stats.
 -- NOTE WELL

 WWP-PORT-STATS-MIB DEFINITIONS ::= BEGIN

 IMPORTS
   Counter64, Unsigned32, Counter32, OBJECT-TYPE, MODULE-IDENTITY
	    FROM SNMPv2-SMI
   wwpModules
	    FROM WWP-SMI;


 wwpPortStatsMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP Port ether Stats."
	    REVISION    "200104031700Z"
	    DESCRIPTION
		    "Initial creation."
	    ::= { wwpModules 16 }

 --
 -- Node definitions
 --

 wwpPortStatsMIBObjects OBJECT IDENTIFIER ::= { wwpPortStatsMIB 1 }


 -- PortStats
 --
 wwpPortStats OBJECT IDENTIFIER ::= { wwpPortStatsMIBObjects 1 }


 -- Notifications

 wwpPortStatsMIBNotificationPrefix  OBJECT IDENTIFIER ::= { wwpPortStatsMIB 2 }
 wwpPortStatsMIBNotifications       OBJECT IDENTIFIER ::=
                       { wwpPortStatsMIBNotificationPrefix 0 }

 -- Conformance information

 wwpPortStatsMIBConformance OBJECT IDENTIFIER ::= { wwpPortStatsMIB 3 }
 wwpPortStatsMIBCompliances OBJECT IDENTIFIER ::= { wwpPortStatsMIBConformance 1 }
 wwpPortStatsMIBGroups      OBJECT IDENTIFIER ::= { wwpPortStatsMIBConformance 2 }


 wwpPortStatsReset OBJECT-TYPE
    SYNTAX          INTEGER {
                        none(0),
	                reset(1)
                    }
    MAX-ACCESS      read-write
    STATUS          deprecated
    DESCRIPTION
	    "To reset the counters related to this port. A read on this object will
            always return the 'none'."
    ::= { wwpPortStats 1 }

 wwpPortStatsTable OBJECT-TYPE
     SYNTAX       SEQUENCE OF WwpPortStatsEntry
     MAX-ACCESS   not-accessible
     STATUS       current
     DESCRIPTION
	     "The table specifying the stats for the ports."
     ::= { wwpPortStats 2 }

 wwpPortStatsEntry OBJECT-TYPE
     SYNTAX       WwpPortStatsEntry
     MAX-ACCESS   not-accessible
     STATUS       current
     DESCRIPTION
	     "An entry in the port stats table."
     INDEX { wwpPortStatsPortId }
     ::= { wwpPortStatsTable 1 }

 WwpPortStatsEntry ::= SEQUENCE {
     wwpPortStatsPortId                INTEGER,
     wwpPortStatsRxBytes               Counter32,
     wwpPortStatsRxPkts                Counter32,
     wwpPortStatsRxCrcErrorPkts        Counter32,
     wwpPortStatsRxBcastPkts           Counter32,
     wwpPortStatsUndersizePkts         Counter32,
     wwpPortStatsOversizePkts          Counter32,
     wwpPortStatsFragmentPkts          Counter32,
     wwpPortStatsJabberPkts            Counter32,
     wwpPortStats64BytePkts            Counter32,
     wwpPortStats65To127BytePkts       Counter32,
     wwpPortStats128To255BytePkts      Counter32,
     wwpPortStats256To511BytePkts      Counter32,
     wwpPortStats512To1023BytePkts     Counter32,
     wwpPortStats1024To1518BytePkts    Counter32,
     wwpPortStatsTxBytes               Counter32,
     wwpPortStatsTxTBytes              Counter32,
     wwpPortStatsTxPkts                Counter32,
     wwpPortStatsTxExDeferPkts         Counter32,
     wwpPortStatsTxGiantPkts           Counter32,
     wwpPortStatsTxUnderRunPkts        Counter32,
     wwpPortStatsTxCrcErrorPkts        Counter32,
     wwpPortStatsTxLCheckErrorPkts     Counter32,
     wwpPortStatsTxLOutRangePkts       Counter32,
     wwpPortStatsTxLateCollPkts        Counter32,
     wwpPortStatsTxExCollPkts          Counter32,
     wwpPortStatsTxSingleCollPkts      Counter32,
     wwpPortStatsTxCollPkts            Counter32
 }

 wwpPortStatsPortId OBJECT-TYPE
    SYNTAX       INTEGER (1..65535)
    MAX-ACCESS   read-only
    STATUS       current
    DESCRIPTION
	    "The Id of the port for which this entry
            contains the stats."
    ::= { wwpPortStatsEntry 1 }

 wwpPortStatsRxBytes OBJECT-TYPE
    SYNTAX        Counter32
    MAX-ACCESS    read-only
    STATUS        current
    DESCRIPTION
	    "The number of bytes received by this port."
    ::= { wwpPortStatsEntry 2 }

 wwpPortStatsRxPkts OBJECT-TYPE
    SYNTAX        Counter32
    MAX-ACCESS    read-only
    STATUS        current
    DESCRIPTION
	    "The number of packets received by this port."
    ::= { wwpPortStatsEntry 3 }

 wwpPortStatsRxCrcErrorPkts OBJECT-TYPE
    SYNTAX        Counter32
    MAX-ACCESS    read-only
    STATUS        current
    DESCRIPTION
	    "The number of packets received with CRC errors by this port."
    ::= { wwpPortStatsEntry 4 }

 wwpPortStatsRxBcastPkts OBJECT-TYPE
    SYNTAX        Counter32
    MAX-ACCESS    read-only
    STATUS        current
    DESCRIPTION
	    "The number of Broadcast packets received by this port."
    ::= { wwpPortStatsEntry 5 }

 wwpPortStatsUndersizePkts OBJECT-TYPE
    SYNTAX        Counter32
    MAX-ACCESS    read-only
    STATUS        current
    DESCRIPTION
            "The total number of packets received that were
            less than 64 octets long (excluding framing bits,
            but including FCS octets) and were otherwise well
            formed."
    ::= { wwpPortStatsEntry 6 }

 wwpPortStatsOversizePkts OBJECT-TYPE
    SYNTAX        Counter32
    MAX-ACCESS    read-only
    STATUS        current
    DESCRIPTION
	    "The total number of packets received that were
            longer than 1518 octets (excluding framing bits,
            but including FCS octets) and were otherwise
            well formed."
    ::= { wwpPortStatsEntry 7 }

 wwpPortStatsFragmentPkts OBJECT-TYPE
    SYNTAX        Counter32
    MAX-ACCESS    read-only
    STATUS        current
    DESCRIPTION
            "The total number of packets received that were less
            than 64 octets in length (excluding framing bits but
            including FCS octets) and had either a bad Frame
            Check Sequence (FCS) with an integral number of
            octets (FCS Error) or a bad FCS with a non-integral
            number of octets (Alignment Error)."
    ::= { wwpPortStatsEntry 8 }


 wwpPortStatsJabberPkts OBJECT-TYPE
    SYNTAX        Counter32
    MAX-ACCESS    read-only
    STATUS        current
    DESCRIPTION
	    "The total number of packets received that were
            longer than 1518 octets (excluding framing bits,
            but including FCS octets), and had either a bad
            Frame Check Sequence (FCS) with an integral number
            of octets (FCS Error) or a bad FCS with a
            non-integral number of octets (Alignment Error)."
    ::= { wwpPortStatsEntry 9 }


 wwpPortStats64BytePkts OBJECT-TYPE
    SYNTAX        Counter32
    MAX-ACCESS    read-only
    STATUS        current
    DESCRIPTION
            "The total number of packets (including bad
            packets) received that were 64 octets in length
            (excluding framing bits but including FCS octets)."
    ::= { wwpPortStatsEntry 10 }


 wwpPortStats65To127BytePkts OBJECT-TYPE
    SYNTAX        Counter32
    MAX-ACCESS    read-only
    STATUS        current
    DESCRIPTION
            "The total number of packets (including bad
            packets) received that were between
            65 and 127 octets in length inclusive
            (excluding framing bits but including FCS octets)."
    ::= { wwpPortStatsEntry 11 }

 wwpPortStats128To255BytePkts OBJECT-TYPE
    SYNTAX        Counter32
    MAX-ACCESS    read-only
    STATUS        current
    DESCRIPTION
	    "The total number of packets (including bad
            packets) received that were between
            128 and 255 octets in length inclusive
            (excluding framing bits but including FCS octets)."
    ::= { wwpPortStatsEntry 12 }

 wwpPortStats256To511BytePkts OBJECT-TYPE
    SYNTAX      Counter32
    MAX-ACCESS  read-only
    STATUS      current
    DESCRIPTION
            "The total number of packets (including bad
            packets) received that were between
            256 and 511 octets in length inclusive
            (excluding framing bits but including FCS octets)."
    ::= { wwpPortStatsEntry 13 }

 wwpPortStats512To1023BytePkts OBJECT-TYPE
    SYNTAX      Counter32
    MAX-ACCESS  read-only
    STATUS      current
    DESCRIPTION
            "The total number of packets (including bad
            packets) received that were between
            512 and 1023 octets in length inclusive
            (excluding framing bits but including FCS octets)."
    ::= { wwpPortStatsEntry 14 }

 wwpPortStats1024To1518BytePkts OBJECT-TYPE
    SYNTAX      Counter32
    MAX-ACCESS  read-only
    STATUS      current
    DESCRIPTION
            "The total number of packets (including bad
            packets) received that were between
            1024 and 1518 octets in length inclusive
            (excluding framing bits but including FCS octets)."
    ::= { wwpPortStatsEntry 15 }

 wwpPortStatsTxBytes OBJECT-TYPE
    SYNTAX      Counter32
    MAX-ACCESS  read-only
    STATUS      current
    DESCRIPTION
	    "The number of Octets transmitted for this port."
    ::= { wwpPortStatsEntry 16 }

 wwpPortStatsTxTBytes OBJECT-TYPE
    SYNTAX      Counter32
    MAX-ACCESS  read-only
    STATUS      current
    DESCRIPTION
	    "The total number of Octets transmitted for this port."
    ::= { wwpPortStatsEntry 17 }

 wwpPortStatsTxPkts OBJECT-TYPE
    SYNTAX      Counter32
    MAX-ACCESS  read-only
    STATUS      current
    DESCRIPTION
	    "The total number of packets transmitted for this port."
    ::= { wwpPortStatsEntry 18 }


 wwpPortStatsTxExDeferPkts OBJECT-TYPE
    SYNTAX      Counter32
    MAX-ACCESS  read-only
    STATUS      current
    DESCRIPTION
            "The transmit excessive defer packet count for a port."
    ::= { wwpPortStatsEntry 19 }

 wwpPortStatsTxGiantPkts OBJECT-TYPE
    SYNTAX      Counter32
    MAX-ACCESS  read-only
    STATUS      current
    DESCRIPTION
	    "The transmit too big packet count for a port."
    ::= { wwpPortStatsEntry 20 }

 wwpPortStatsTxUnderRunPkts OBJECT-TYPE
    SYNTAX      Counter32
    MAX-ACCESS  read-only
    STATUS      current
    DESCRIPTION
            "The transmit underrun packet count for a port."
    ::= { wwpPortStatsEntry 21 }

 wwpPortStatsTxCrcErrorPkts OBJECT-TYPE
    SYNTAX      Counter32
    MAX-ACCESS  read-only
    STATUS      current
    DESCRIPTION
            "The transmit CRC error packet count for a port."
    ::= { wwpPortStatsEntry 22 }

 wwpPortStatsTxLCheckErrorPkts OBJECT-TYPE
    SYNTAX      Counter32
    MAX-ACCESS  read-only
    STATUS      current
    DESCRIPTION
	    "The transmit length check error packet count for a port."
    ::= { wwpPortStatsEntry 23 }

 wwpPortStatsTxLOutRangePkts OBJECT-TYPE
    SYNTAX      Counter32
    MAX-ACCESS  read-only
    STATUS      current
    DESCRIPTION
	    "The transmit length out of range packet count for a port."
    ::= { wwpPortStatsEntry 24 }

 wwpPortStatsTxLateCollPkts OBJECT-TYPE
    SYNTAX      Counter32
    MAX-ACCESS  read-only
    STATUS      current
    DESCRIPTION
	    "The transmit late collision packet count for a port."
    ::= { wwpPortStatsEntry 25 }

 wwpPortStatsTxExCollPkts OBJECT-TYPE
    SYNTAX      Counter32
    MAX-ACCESS  read-only
    STATUS      current
    DESCRIPTION
	    "The transmit excessive collision packet count for a port."
    ::= { wwpPortStatsEntry 26 }

 wwpPortStatsTxSingleCollPkts OBJECT-TYPE
    SYNTAX      Counter32
    MAX-ACCESS  read-only
    STATUS      current
    DESCRIPTION
	    "The transmit single collision packet count for a port."
    ::= { wwpPortStatsEntry 27 }

 wwpPortStatsTxCollPkts OBJECT-TYPE
    SYNTAX       Counter32
    MAX-ACCESS   read-only
    STATUS       current
    DESCRIPTION
	    "The transmit collision packet count for a port."
    ::= { wwpPortStatsEntry 28 }

 --
 -- Extension to the port Stats Table
 --

 wwpPortStatsXTable OBJECT-TYPE
     SYNTAX       SEQUENCE OF WwpPortStatsXEntry
     MAX-ACCESS   not-accessible
     STATUS       current
     DESCRIPTION
	     "The table extending the stats for the ports to 64 bits."
     ::= { wwpPortStats 3 }

 wwpPortStatsXEntry OBJECT-TYPE
     SYNTAX       WwpPortStatsXEntry
     MAX-ACCESS   not-accessible
     STATUS       current
     DESCRIPTION
	     "An entry in the port stats extension table."
     INDEX { wwpPortStatsPortId }
     ::= { wwpPortStatsXTable 1 }

 WwpPortStatsXEntry ::= SEQUENCE {
     wwpPortStatsXRxBytes       Counter64,
     wwpPortStatsXRxPkts        Counter64,
     wwpPortStatsXTxBytes       Counter64,
     wwpPortStatsXTxPkts        Counter64
 }

 wwpPortStatsXRxBytes OBJECT-TYPE
    SYNTAX        Counter64
    MAX-ACCESS    read-only
    STATUS        current
    DESCRIPTION
	    "The number of bytes received by this port."
    ::= { wwpPortStatsXEntry 1 }

 wwpPortStatsXRxPkts OBJECT-TYPE
    SYNTAX        Counter64
    MAX-ACCESS    read-only
    STATUS        current
    DESCRIPTION
	    "The number of packets received by this port."
    ::= { wwpPortStatsXEntry 2 }

 wwpPortStatsXTxBytes OBJECT-TYPE
    SYNTAX      Counter64
    MAX-ACCESS  read-only
    STATUS      current
    DESCRIPTION
	    "The total number of Bytes transmitted for this port."
    ::= { wwpPortStatsXEntry 3 }

 wwpPortStatsXTxPkts OBJECT-TYPE
    SYNTAX      Counter64
    MAX-ACCESS  read-only
    STATUS      current
    DESCRIPTION
	    "The total number of packets transmitted for this port."
    ::= { wwpPortStatsXEntry 4 }

--
-- Extension to the port Stats with 32 bit counters to support v1
--

 wwpPortStatsPortalTable OBJECT-TYPE
     SYNTAX       SEQUENCE OF WwpPortStatsPortalEntry
     MAX-ACCESS   not-accessible
     STATUS       current
     DESCRIPTION
	     "The table extending the statistic counters for the ports to 64 bits."
     ::= { wwpPortStats 4 }

 wwpPortStatsPortalEntry OBJECT-TYPE
     SYNTAX       WwpPortStatsPortalEntry
     MAX-ACCESS   not-accessible
     STATUS       current
     DESCRIPTION
	     "An entry in the port stats extension table."
     INDEX { wwpPortStatsPortalPortId }
     ::= { wwpPortStatsPortalTable 1 }

 WwpPortStatsPortalEntry ::= SEQUENCE {
     wwpPortStatsPortalPortId                        INTEGER,

     wwpPortStatsPortalBytesSentHi		     Counter32,
     wwpPortStatsPortalBytesSentLo		     Counter32,

     wwpPortStatsPortalFlowControlHi                 Counter32,
     wwpPortStatsPortalFlowControlLo                 Counter32,

     wwpPortStatsPortalUnicastFramesSentHi	     Counter32,
     wwpPortStatsPortalUnicastFramesSentLo           Counter32,

     wwpPortStatsPortalAlignmentErrorHi              Counter32,
     wwpPortStatsPortalAlignmentErrorLo              Counter32,

     wwpPortStatsPortalNonUnicastFramesSentHi        Counter32,
     wwpPortStatsPortalNonUnicastFramesSentLo        Counter32,

     wwpPortStatsPortalTotalBytesRecievedHi          Counter32,
     wwpPortStatsPortalTotalBytesRecievedLo          Counter32,

     wwpPortStatsPortalFlowControlFramesRecievedHi   Counter32,
     wwpPortStatsPortalFlowControlFramesRecievedLo   Counter32,

     wwpPortStatsPortalTotalFramesRecievedHi         Counter32,
     wwpPortStatsPortalTotalFramesRecievedLo         Counter32,

     wwpPortStatsPortalBroadcastFramesRecievedHi     Counter32,
     wwpPortStatsPortalBroadcastFramesRecievedLo     Counter32,

     wwpPortStatsPortalMulticastFramesRecievedHi     Counter32,
     wwpPortStatsPortalMulticastFramesRecievedLo     Counter32,

     wwpPortStatsPortalJabberFramesHi                Counter32,
     wwpPortStatsPortalJabberFramesLo                Counter32,

     wwpPortStatsPortal64ByteFramesHi                Counter32,
     wwpPortStatsPortal64ByteFramesLo                Counter32,

     wwpPortStatsPortalOversizeFramesHi              Counter32,
     wwpPortStatsPortalOversizeFramesLo	       	     Counter32,

     wwpPortStatsPortal65To127ByteFramesHi           Counter32,
     wwpPortStatsPortal65To127ByteFramesLo           Counter32,

     wwpPortStatsPortal256To511ByteFramesHi          Counter32,
     wwpPortStatsPortal256To511ByteFramesLo          Counter32,

     wwpPortStatsPortal128To255ByteFramesHi          Counter32,
     wwpPortStatsPortal128To255ByteFramesLo          Counter32,

     wwpPortStatsPortal1024To1528ByteFramesHi        Counter32,
     wwpPortStatsPortal1024To1528ByteFramesLo        Counter32,

     wwpPortStatsPortal512To1023ByteFramesHi         Counter32,
     wwpPortStatsPortal512To1023ByteFrameslo         Counter32,

     wwpPortStatsPortalFragmentHi                    Counter32,
     wwpPortStatsPortalFragmentLo                    Counter32,

     wwpPortStatsPortalUndersizeFramesHi             Counter32,
     wwpPortStatsPortalUndersizeFramesLo             Counter32,

     wwpPortStatsPortalShortEventHi                  Counter32,
     wwpPortStatsPortalShortEventLo                  Counter32,

     wwpPortStatsPortalCRCHi                         Counter32,
     wwpPortStatsPortalCRCLo                         Counter32,

     wwpPortStatsPortalDroppedFramesHi               Counter32,
     wwpPortStatsPortalDroppedFramesLo               Counter32,

     wwpPortStatsPortalCollisionHi                   Counter32,
     wwpPortStatsPortalCollisionLo                   Counter32,

     wwpPortStatsPortalLateCollisionHi               Counter32,
     wwpPortStatsPortalLateCollisionLo               Counter32,

     wwpPortStatsPortalFilteringCounterHi            Counter32,
     wwpPortStatsPortalFilteringCounterLo            Counter32
}

 wwpPortStatsPortalPortId OBJECT-TYPE
    SYNTAX       INTEGER (1..65535)
    MAX-ACCESS   read-only
    STATUS       current
    DESCRIPTION
	    "The Id of the port for which this entry
            contains the stats."
    ::= { wwpPortStatsPortalEntry 1 }

 wwpPortStatsPortalBytesSentHi OBJECT-TYPE
    SYNTAX	Counter32
    MAX-ACCESS	read-only
    STATUS	current
    DESCRIPTION
	    "The number of bytes sent from this port.
	     This element represents the upper 32-bits of
	     a 64-bit counter."
    ::= { wwpPortStatsPortalEntry 2 }

 wwpPortStatsPortalBytesSentLo OBJECT-TYPE
    SYNTAX	Counter32
    MAX-ACCESS	read-only
    STATUS	current
    DESCRIPTION
	    "The number of bytes sent from this port.
	     This element represents the lower 32-bits of
	     a 64-bit counter."
    ::= { wwpPortStatsPortalEntry 3 }

 wwpPortStatsPortalFlowControlHi OBJECT-TYPE
    SYNTAX	Counter32
    MAX-ACCESS	read-only
    STATUS	current
    DESCRIPTION
	    "The number of Flow Control frames sent from
	     this port. This element represents the
	     upper 32-bits of a 64-bit counter."
    ::= { wwpPortStatsPortalEntry 4 }

 wwpPortStatsPortalFlowControlLo OBJECT-TYPE
    SYNTAX	Counter32
    MAX-ACCESS	read-only
    STATUS	current
    DESCRIPTION
	    "The number of Flow Control frames sent from
	     this port. This element represents the
	     lower 32-bits of a 64-bit counter."
    ::= { wwpPortStatsPortalEntry 5 }

 wwpPortStatsPortalUnicastFramesSentHi OBJECT-TYPE
    SYNTAX	Counter32
    MAX-ACCESS	read-only
    STATUS	current
    DESCRIPTION
	    "The number of Unicast Frames sent from
	     this port. This element represents the
	     upper 32-bits of a 64-bit counter."
    ::= { wwpPortStatsPortalEntry 6 }

 wwpPortStatsPortalUnicastFramesSentLo OBJECT-TYPE
    SYNTAX	Counter32
    MAX-ACCESS	read-only
    STATUS	current
    DESCRIPTION
	    "The number of Unicast Frames sent from
	     this port. This element represents the
	     lower 32-bits of a 64-bit counter."
    ::= { wwpPortStatsPortalEntry 7 }

 wwpPortStatsPortalAlignmentErrorHi OBJECT-TYPE
    SYNTAX	Counter32
    MAX-ACCESS	read-only
    STATUS	current
    DESCRIPTION
	    "A count of frames that are not an integral
	     number of octets in length and do not pass
	     the FCS check. This counter is incremented
	     when the Receive-Status is reported as
	     Alignment-Error. This element represents the
	     upper 32-bits of a 64-bit counter."
    ::= { wwpPortStatsPortalEntry 8 }

 wwpPortStatsPortalAlignmentErrorLo OBJECT-TYPE
    SYNTAX	Counter32
    MAX-ACCESS	read-only
    STATUS	current
    DESCRIPTION
	    "The number of frames that are not an integral
	     number of octets in length and do not pass
	     the FCS check. This counter is incremented
	     when the Receive-Status is reported as
	     Alignment-Error. This element represents the
	     lower 32-bits of a 64-bit counter."
    ::= { wwpPortStatsPortalEntry 9 }

 wwpPortStatsPortalNonUnicastFramesSentHi OBJECT-TYPE
    SYNTAX	Counter32
    MAX-ACCESS	read-only
    STATUS	current
    DESCRIPTION
	    "The number of non-unicast frames sent from this
	     port. This element represents the upper 32-bits
	     of a 64-bit counter."
    ::= { wwpPortStatsPortalEntry 10 }

 wwpPortStatsPortalNonUnicastFramesSentLo OBJECT-TYPE
    SYNTAX	Counter32
    MAX-ACCESS	read-only
    STATUS	current
    DESCRIPTION
	    "The number of non-unicast frames sent from this
	     port. This element represents the lower 32-bits
	     of a 64-bit counter."
    ::= { wwpPortStatsPortalEntry 11 }

 wwpPortStatsPortalTotalBytesRecievedHi OBJECT-TYPE
    SYNTAX	Counter32
    MAX-ACCESS	read-only
    STATUS	current
    DESCRIPTION
	    "The total number of bytes recieved on this port.
	     This element represents the upper 32-bits of a
	     64-bit counter."
    ::= { wwpPortStatsPortalEntry 12 }

 wwpPortStatsPortalTotalBytesRecievedLo OBJECT-TYPE
    SYNTAX	Counter32
    MAX-ACCESS	read-only
    STATUS	current
    DESCRIPTION
	    "The total number of bytes recieved on this port.
	     This element represents the upper 32-bits of a
	     64-bit counter."
    ::= { wwpPortStatsPortalEntry 13 }

 wwpPortStatsPortalFlowControlFramesRecievedHi OBJECT-TYPE
    SYNTAX	Counter32
    MAX-ACCESS	read-only
    STATUS	current
    DESCRIPTION
	    "The number of flow control frames recieved.
	     This element represents the upper 32-bits of a
	     64-bit counter."
    ::= { wwpPortStatsPortalEntry 14 }

 wwpPortStatsPortalFlowControlFramesRecievedLo OBJECT-TYPE
    SYNTAX	Counter32
    MAX-ACCESS	read-only
    STATUS	current
    DESCRIPTION
	    "The number of flow control frames recieved.
	     This element represents the lower 32-bits of a
	     64-bit counter."
    ::= { wwpPortStatsPortalEntry 15 }

 wwpPortStatsPortalTotalFramesRecievedHi OBJECT-TYPE
    SYNTAX	Counter32
    MAX-ACCESS	read-only
    STATUS	current
    DESCRIPTION
	    "The total number of frames recieved on this
	     port. This element represents the upper 32-bits
	     of a 64-bit counter."
    ::= { wwpPortStatsPortalEntry 16 }

 wwpPortStatsPortalTotalFramesRecievedLo OBJECT-TYPE
    SYNTAX	Counter32
    MAX-ACCESS	read-only
    STATUS	current
    DESCRIPTION
	    "The total number of frames recieved on this
	     port. This element represents the lower 32-bits
	     of a 64-bit counter."
    ::= { wwpPortStatsPortalEntry 17 }

 wwpPortStatsPortalBroadcastFramesRecievedHi OBJECT-TYPE
    SYNTAX	Counter32
    MAX-ACCESS	read-only
    STATUS	current
    DESCRIPTION
	    "The number of broadcast frames recieved on
	     this port. This element represents the upper
	     32-bits of a 64-bit counter."
    ::= { wwpPortStatsPortalEntry 18 }

 wwpPortStatsPortalBroadcastFramesRecievedLo OBJECT-TYPE
    SYNTAX	Counter32
    MAX-ACCESS	read-only
    STATUS	current
    DESCRIPTION
	    "The number of broadcast frames recieved on
	     this port. This element represents the lower
	     32-bits of a 64-bit counter."
    ::= { wwpPortStatsPortalEntry 19 }

 wwpPortStatsPortalMulticastFramesRecievedHi OBJECT-TYPE
    SYNTAX	Counter32
    MAX-ACCESS	read-only
    STATUS	current
    DESCRIPTION
	    "The number of multicast frames recieved on
	     this port. This element represents the upper
	     32-bits of a 64-bit counter."
    ::= { wwpPortStatsPortalEntry 20 }

 wwpPortStatsPortalMulticastFramesRecievedLo OBJECT-TYPE
    SYNTAX	Counter32
    MAX-ACCESS	read-only
    STATUS	current
    DESCRIPTION
	    "The number of multicast frames recieved on
	     this port. This element represents the lower
	     32-bits of a 64-bit counter."
    ::= { wwpPortStatsPortalEntry 21 }

 wwpPortStatsPortalJabberFramesHi OBJECT-TYPE
    SYNTAX	Counter32
    MAX-ACCESS	read-only
    STATUS	current
    DESCRIPTION
	    "The total number of packets received that were
             longer than 1518 octets (excluding framing bits,
             but including FCS octets), and had either a bad
             Frame Check Sequence (FCS) with an integral number
             of octets (FCS Error) or a bad FCS with a
             non-integral number of octets (Alignment Error).
	     This element represents the upper 32-bits of a
	     64-bit counter."
    ::= { wwpPortStatsPortalEntry 22 }

 wwpPortStatsPortalJabberFramesLo OBJECT-TYPE
    SYNTAX	Counter32
    MAX-ACCESS	read-only
    STATUS	current
    DESCRIPTION
	    "The total number of packets received that were
             longer than 1518 octets (excluding framing bits,
             but including FCS octets), and had either a bad
             Frame Check Sequence (FCS) with an integral number
             of octets (FCS Error) or a bad FCS with a
             non-integral number of octets (Alignment Error).
	     This element represents the lower 32-bits of a
	     64-bit counter."
    ::= { wwpPortStatsPortalEntry 23 }

 wwpPortStatsPortal64ByteFramesHi OBJECT-TYPE
    SYNTAX	Counter32
    MAX-ACCESS	read-only
    STATUS	current
    DESCRIPTION
	    "The total number of packets (including bad
             packets) received that were 64 octets in length
             (excluding framing bits but including FCS octets).
	     This element represents the upper 32-bits of a
	     64-bit counter."
    ::= { wwpPortStatsPortalEntry 24 }

 wwpPortStatsPortal64ByteFramesLo OBJECT-TYPE
    SYNTAX	Counter32
    MAX-ACCESS	read-only
    STATUS	current
    DESCRIPTION
	    "The total number of packets (including bad
             packets) received that were 64 octets in length
             (excluding framing bits but including FCS octets).
	     This element represents the lower 32-bits of a
	     64-bit counter."
    ::= { wwpPortStatsPortalEntry 25 }

 wwpPortStatsPortalOversizeFramesHi OBJECT-TYPE
    SYNTAX	Counter32
    MAX-ACCESS	read-only
    STATUS	current
    DESCRIPTION
	    ""
    ::= { wwpPortStatsPortalEntry 26 }

 wwpPortStatsPortalOversizeFramesLo OBJECT-TYPE
    SYNTAX	Counter32
    MAX-ACCESS	read-only
    STATUS	current
    DESCRIPTION
	    ""
    ::= { wwpPortStatsPortalEntry 27 }

 wwpPortStatsPortal65To127ByteFramesHi OBJECT-TYPE
    SYNTAX	Counter32
    MAX-ACCESS	read-only
    STATUS	current
    DESCRIPTION
	    "The total number of packets (including bad
             packets) received that were between
             65 and 127 octets in length inclusive
             (excluding framing bits but including FCS octets).
	     This element represents the upper 32-bits of a
	     64-bit counter."
    ::= { wwpPortStatsPortalEntry 28 }

 wwpPortStatsPortal65To127ByteFramesLo OBJECT-TYPE
    SYNTAX	Counter32
    MAX-ACCESS	read-only
    STATUS	current
    DESCRIPTION
	    "The total number of packets (including bad
             packets) received that were between
             65 and 127 octets in length inclusive
             (excluding framing bits but including FCS octets).
	     This element represents the lower 32-bits of a
	     64-bit counter."
    ::= { wwpPortStatsPortalEntry 29 }

 wwpPortStatsPortal256To511ByteFramesHi OBJECT-TYPE
    SYNTAX	Counter32
    MAX-ACCESS	read-only
    STATUS	current
    DESCRIPTION
	    "The total number of packets (including bad
             packets) received that were between
             256 and 511 octets in length inclusive
             (excluding framing bits but including FCS octets).
	     This element represents the upper 32-bits of a
	     64-bit counter."
    ::= { wwpPortStatsPortalEntry 30 }

 wwpPortStatsPortal256To511ByteFramesLo OBJECT-TYPE
    SYNTAX	Counter32
    MAX-ACCESS	read-only
    STATUS	current
    DESCRIPTION
	    "The total number of packets (including bad
             packets) received that were between
             256 and 511 octets in length inclusive
             (excluding framing bits but including FCS octets).
	     This element represents the lower 32-bits of a
	     64-bit counter."
    ::= { wwpPortStatsPortalEntry 31 }

 wwpPortStatsPortal128To255ByteFramesHi OBJECT-TYPE
    SYNTAX	Counter32
    MAX-ACCESS	read-only
    STATUS	current
    DESCRIPTION
	    "The total number of packets (including bad
             packets) received that were between
             128 and 255 octets in length inclusive
             (excluding framing bits but including FCS octets).
	     This element represents the upper 32-bits of a
	     64-bit counter."
    ::= { wwpPortStatsPortalEntry 32 }

 wwpPortStatsPortal128To255ByteFramesLo OBJECT-TYPE
    SYNTAX	Counter32
    MAX-ACCESS	read-only
    STATUS	current
    DESCRIPTION
	    "The total number of packets (including bad
             packets) received that were between
             128 and 255 octets in length inclusive
             (excluding framing bits but including FCS octets).
	     This element represents the lower 32-bits of a
	     64-bit counter."
    ::= { wwpPortStatsPortalEntry 33 }

 wwpPortStatsPortal1024To1528ByteFramesHi OBJECT-TYPE
    SYNTAX	Counter32
    MAX-ACCESS	read-only
    STATUS	current
    DESCRIPTION
	    "The total number of packets (including bad
             packets) received that were between
             1024 and 1528 octets in length inclusive
             (excluding framing bits but including FCS octets)
	     This element represents the upper 32-bits of a
	     64-bit counter."
    ::= { wwpPortStatsPortalEntry 34 }

 wwpPortStatsPortal1024To1528ByteFramesLo OBJECT-TYPE
    SYNTAX	Counter32
    MAX-ACCESS	read-only
    STATUS	current
    DESCRIPTION
	    "The total number of packets (including bad
             packets) received that were between
             1024 and 1528 octets in length inclusive
             (excluding framing bits but including FCS octets)
	     This element represents the lower 32-bits of a
	     64-bit counter."
    ::= { wwpPortStatsPortalEntry 35 }

 wwpPortStatsPortal512To1023ByteFramesHi OBJECT-TYPE
    SYNTAX	Counter32
    MAX-ACCESS	read-only
    STATUS	current
    DESCRIPTION
	    "The total number of packets (including bad
             packets) received that were between
             512 and 1023 octets in length inclusive
             (excluding framing bits but including FCS octets).
	     This element represents the upper 32-bits of a
	     64-bit counter."
    ::= { wwpPortStatsPortalEntry 36 }

 wwpPortStatsPortal512To1023ByteFrameslo OBJECT-TYPE
    SYNTAX	Counter32
    MAX-ACCESS	read-only
    STATUS	current
    DESCRIPTION
	    "The total number of packets (including bad
             packets) received that were between
             512 and 1023 octets in length inclusive
             (excluding framing bits but including FCS octets).
	     This element represents the lower 32-bits of a
	     64-bit counter."
    ::= { wwpPortStatsPortalEntry 37 }

 wwpPortStatsPortalFragmentHi OBJECT-TYPE
    SYNTAX	Counter32
    MAX-ACCESS	read-only
    STATUS	current
    DESCRIPTION
	    "The number of fragmented frames recieved by
	     this port. This element represents the lower
	     32-bits of a 64-bit counter."
    ::= { wwpPortStatsPortalEntry 38 }

 wwpPortStatsPortalFragmentLo OBJECT-TYPE
    SYNTAX	Counter32
    MAX-ACCESS	read-only
    STATUS	current
    DESCRIPTION
	    "The number of fragmented frames recieved by
	     this port. This element represents the lower
	     32-bits of a 64-bit counter."
    ::= { wwpPortStatsPortalEntry 39 }

 wwpPortStatsPortalUndersizeFramesHi OBJECT-TYPE
    SYNTAX	Counter32
    MAX-ACCESS	read-only
    STATUS	current
    DESCRIPTION
	    "The number of undersized frames recieved by
	     this port. This element represents the upper
	     32-bits of a 64-bit counter."
    ::= { wwpPortStatsPortalEntry 40 }

 wwpPortStatsPortalUndersizeFramesLo OBJECT-TYPE
    SYNTAX	Counter32
    MAX-ACCESS	read-only
    STATUS	current
    DESCRIPTION
	    "The number of undersized frames recieved by
	     this port. This element represents the lower
	     32-bits of a 64-bit counter."
    ::= { wwpPortStatsPortalEntry 41 }

 wwpPortStatsPortalShortEventHi OBJECT-TYPE
    SYNTAX	Counter32
    MAX-ACCESS	read-only
    STATUS	current
    DESCRIPTION
	    "Short event counter. This element represents
	     the upper 32-bits of a 64-bit counter."
    ::= { wwpPortStatsPortalEntry 42 }

 wwpPortStatsPortalShortEventLo OBJECT-TYPE
    SYNTAX	Counter32
    MAX-ACCESS	read-only
    STATUS	current
    DESCRIPTION
	    "Short event counter. This element represents
	     the lower 32-bits of a 64-bit counter."
    ::= { wwpPortStatsPortalEntry 43 }

 wwpPortStatsPortalCRCHi OBJECT-TYPE
    SYNTAX	Counter32
    MAX-ACCESS	read-only
    STATUS	current
    DESCRIPTION
	    "The number of CRC error frames recieved
	     by a given port. This element represents the upper
	     32-bits of a 64-bit counter."
    ::= { wwpPortStatsPortalEntry 44 }

 wwpPortStatsPortalCRCLo OBJECT-TYPE
    SYNTAX	Counter32
    MAX-ACCESS	read-only
    STATUS	current
    DESCRIPTION
	    "The number of CRC error frames recieved
	     by a given port. This element represents the lower
	     32-bits of a 64-bit counter."
    ::= { wwpPortStatsPortalEntry 45 }

 wwpPortStatsPortalDroppedFramesHi OBJECT-TYPE
    SYNTAX	Counter32
    MAX-ACCESS	read-only
    STATUS	current
    DESCRIPTION
	    "The number of frames dropped by a given port.
	     This element represents the upper 32-bits
	     of a 64-bit counter."
    ::= { wwpPortStatsPortalEntry 46 }

 wwpPortStatsPortalDroppedFramesLo OBJECT-TYPE
    SYNTAX	Counter32
    MAX-ACCESS	read-only
    STATUS	current
    DESCRIPTION
	    "The number of frames dropped by a given port.
	     This element represents the lower 32-bits
	     of a 64-bit counter."
    ::= { wwpPortStatsPortalEntry 47 }

 wwpPortStatsPortalCollisionHi OBJECT-TYPE
    SYNTAX	Counter32
    MAX-ACCESS	read-only
    STATUS	current
    DESCRIPTION
	    "The number of frames that are involved in a
	     collision. This element represents the upper
	     32-bits of a 64-bit counter."
    ::= { wwpPortStatsPortalEntry 48 }

 wwpPortStatsPortalCollisionLo OBJECT-TYPE
    SYNTAX	Counter32
    MAX-ACCESS	read-only
    STATUS	current
    DESCRIPTION
	    "The number of frames that are involved in a
	     collision. This element represents the lower
	     32-bits of a 64-bit counter."
    ::= { wwpPortStatsPortalEntry 49 }

 wwpPortStatsPortalLateCollisionHi OBJECT-TYPE
    SYNTAX	Counter32
    MAX-ACCESS	read-only
    STATUS	current
    DESCRIPTION
	    "A count of the times that a collision has been
	     detected later than 512 bit times into the transmitted
	     packet. A late collision is counted twice, i.e., both
	     as a collision and as a late-collision. This element
	     represents the upper 32-bits of a 64-bit counter."
    ::= { wwpPortStatsPortalEntry 50 }

 wwpPortStatsPortalLateCollisionLo OBJECT-TYPE
    SYNTAX	Counter32
    MAX-ACCESS	read-only
    STATUS	current
    DESCRIPTION
	    "A count of the times that a collision has been
	     detected later than 512 bit times into the transmitted
	     packet. A late collision is counted twice, i.e., both
	     as a collision and as a late-collision. This element
	     represents the lower 32-bits of a 64-bit counter."
    ::= { wwpPortStatsPortalEntry 51 }

 wwpPortStatsPortalFilteringCounterHi OBJECT-TYPE
    SYNTAX	Counter32
    MAX-ACCESS	read-only
    STATUS	current
    DESCRIPTION
    -- description needs work...
	    "Filtering counter. This element represents
	     the upper 32-bits of a 64-bit counter."
    ::= { wwpPortStatsPortalEntry 52 }

 wwpPortStatsPortalFilteringCounterLo OBJECT-TYPE
    SYNTAX	Counter32
    MAX-ACCESS	read-only
    STATUS	current
    DESCRIPTION
	    "Filtering counter. This element represents
	     the lower 32-bits of a 64-bit counter."
    ::= { wwpPortStatsPortalEntry 53 }

END
