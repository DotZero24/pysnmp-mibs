--
 -- WWP-CONTAINMENT-MIB.my
 --
 --

 WWP-CONTAINMENT-MIB DEFINITIONS ::= BEGIN

 IMPORTS
   NOTIFICATION-TYPE, IpAddress, Integer32, Unsigned32, OBJECT-TYPE, MODULE-IDENTITY
	    FROM SNMPv2-SMI
   DisplayString, MacAddress, DateAndTime, RowStatus, TruthValue
	    FROM SNMPv2-TC
   wwpModules
	    FROM WWP-SMI;


 wwpContainmentMIB MODULE-IDENTITY
	    LAST-UPDATED "200506091700Z"
	    ORGANIZATION "World Wide Packets, Inc"
 	    CONTACT-INFO
		    "   Mib Meister
		  	Postal: World Wide Packets
		        P.O. Box 950
		        Veradale, WA 99037
		        USA
		 	Phone:  +1 509 242 9000
			Email:  mib.meister@worldwidepackets.com"
	    DESCRIPTION
		    "This MIB contains objects that control packet containment
		    within the device.  This MIB deals with packet containment
		    on a per-port basis using Link Shaping containment mechanisms."
	    ::= { wwpModules 55 }


 --
 -- Textual conventions
 --


 --
 -- Node definitions
 --

 wwpContainmentMIBObjects OBJECT IDENTIFIER ::= { wwpContainmentMIB 1 }

 --
 -- System Atributes
 --
 wwpContainment OBJECT IDENTIFIER ::= { wwpContainmentMIBObjects 1 }


 -- Notifications

 wwpContainmentMIBNotificationPrefix  OBJECT IDENTIFIER ::= { wwpContainmentMIB 2 }
 wwpContainmentMIBNotifications       OBJECT IDENTIFIER ::=
                       { wwpContainmentMIBNotificationPrefix 0 }

 -- Conformance information

 wwpContainmentMIBConformance OBJECT IDENTIFIER ::= { wwpContainmentMIB 3 }
 wwpContainmentMIBCompliances OBJECT IDENTIFIER ::= { wwpContainmentMIBConformance 1 }
 wwpContainmentMIBGroups      OBJECT IDENTIFIER ::= { wwpContainmentMIBConformance 2 }


 --
 --  The Containment Broadcast Table
 --

 wwpContainmentBroadcastTable OBJECT-TYPE
     SYNTAX     SEQUENCE OF WwpContainmentBroadcastEntry
     MAX-ACCESS not-accessible
     STATUS     current
     DESCRIPTION
            "The (conceptual) table listing the broadcast
            containment settings per port."
    ::= { wwpContainment 1 }

 wwpContainmentBroadcastEntry OBJECT-TYPE
    SYNTAX     WwpContainmentBroadcastEntry
    MAX-ACCESS not-accessible
    STATUS     current
    DESCRIPTION
            "An entry (conceptual row) in the wwpContainmentBroadcastTable."
    INDEX      { wwpContainmentBroadcastPortId }
    ::= { wwpContainmentBroadcastTable 1 }


 WwpContainmentBroadcastEntry ::= SEQUENCE {
    wwpContainmentBroadcastPortId           INTEGER,
    wwpContainmentBroadcastAction           INTEGER,
    wwpContainmentBroadcastHighMark         Integer32,
    wwpContainmentBroadcastLowMark          Integer32,
    wwpContainmentBroadcastTrapsEnable      TruthValue,
    wwpContainmentBroadcastState            INTEGER
 }

 wwpContainmentBroadcastPortId OBJECT-TYPE
    SYNTAX       INTEGER (1..65535)
    MAX-ACCESS   read-only
    STATUS       current
    DESCRIPTION
	    "The Id of the port for which this entry contains the containment
	    settings.  This value corresponds to the same portId for this port
	    defined in the object wwpPortStatsPortId as defined in the MIB
	    wwpPortStatsMIB."
      ::= { wwpContainmentBroadcastEntry 1 }

 wwpContainmentBroadcastAction  OBJECT-TYPE
     SYNTAX           INTEGER {
                        disable(1),
                        monitor(2),
                        throttle(3)
                      }
     MAX-ACCESS      read-write
     STATUS          current
     DESCRIPTION
       "This value defines the action that is associated
       with the broadcast containment mechanism for this port.

       When this object contains the value of disable(1),
       then all broadcast containment activity for this port
       is disabled.

       When this object contains the value of monitor(1),
       then the broadcast containment mechanism will not
       inhibit packet forwarding on this port while the
       broadcast containment mechanism is engaged. This
       setting is useful for monitoring SNMP traps that may
       be generated by the broadcast containment mechanism.

       When this object contains the value of throttle(2),
       then the broadcast containment mechanism will inhibit
       packet forwarding on this port while the broadcast
       containment mechanism is engaged."
       DEFVAL { 1 }
       ::= { wwpContainmentBroadcastEntry 2 }


 wwpContainmentBroadcastHighMark  OBJECT-TYPE
     SYNTAX          Integer32(0..2147483647)
     MAX-ACCESS      read-write
     STATUS          current
     DESCRIPTION
	    "The value which must be reached or exceeded to trigger
	    the engagement of the broadcast containment mechanism.

	    To prevent containment engagement lockup, the broadcast
	    containment mechanism will not engage if the value of
	    this is less than or equal to the value specified in
	    wwpContainmentBroadcastLowMark.

	    This value refers to the number of ingressing
	    frames-per-second."
       ::= { wwpContainmentBroadcastEntry 3 }

 wwpContainmentBroadcastLowMark  OBJECT-TYPE
     SYNTAX          Integer32(0..2147483647)
     MAX-ACCESS      read-write
     STATUS          current
     DESCRIPTION
        "The value which must be reached or preceded to release
        the engagement of the broadcast containment mechanism.

	    This value refers to the number of ingressing
	    frames-per-second."
       ::= { wwpContainmentBroadcastEntry 4 }

 wwpContainmentBroadcastTrapsEnable  OBJECT-TYPE
     SYNTAX          TruthValue
     MAX-ACCESS      read-write
     STATUS          current
     DESCRIPTION
       "Enables or disables the traps associated with the
       containment mechanism for this port.  When
       set to true, a trap will be sent when the
       broadcast containment mechanism becomes engaged
       and a trap will be sent when the broadcast
       containment mechanism becomes disengaged. When
       set to false, no containment traps will be
       sent from the broadcast containment mechanism
       for this port."
       DEFVAL { true }
       ::= { wwpContainmentBroadcastEntry 5 }

 wwpContainmentBroadcastState OBJECT-TYPE
     SYNTAX           INTEGER {
                        idle(1),
                        starting(2),
                        engaged(3),
                        stopping(4)
                      }
     MAX-ACCESS      read-only
     STATUS          current
     DESCRIPTION
       "This value indicates the present state of the
       broadcast containment mechanism within the device.

       idle(1) - The broadcast containment is presently
       disengaged.

       starting(2) - The broadcast containment mechanism has
       determined that the conditions warrant the engagement
       of the broadcast containment mechanism.  This is a
       momentary state which may exist during the transition
       from the idle state to the engaged state.

       engaged(3) - The broadcast containment mechanism is
       currently engaged.  The action defined by
       wwpContainmentBroadcastAction is presently in effect.

       stopping(4) - The broadcast containment mechanism has
       determined that the conditions warrant the disengagement
       of the broadcast containment mechanism.  This is a
       momentary state which may exist during the transition
       from the engaged state to the idle state."
       ::= { wwpContainmentBroadcastEntry 6 }




 --
 --  The Containment Multicast Table
 --

 wwpContainmentMulticastTable OBJECT-TYPE
     SYNTAX     SEQUENCE OF WwpContainmentMulticastEntry
     MAX-ACCESS not-accessible
     STATUS     current
     DESCRIPTION
            "The (conceptual) table listing the multicast
            containment settings per port."
    ::= { wwpContainment 2 }

 wwpContainmentMulticastEntry OBJECT-TYPE
    SYNTAX     WwpContainmentMulticastEntry
    MAX-ACCESS not-accessible
    STATUS     current
    DESCRIPTION
            "An entry (conceptual row) in the wwpContainmentMulticastTable."
    INDEX      { wwpContainmentMulticastPortId }
    ::= { wwpContainmentMulticastTable 1 }


 WwpContainmentMulticastEntry ::= SEQUENCE {
    wwpContainmentMulticastPortId           INTEGER,
    wwpContainmentMulticastAction           INTEGER,
    wwpContainmentMulticastHighMark         Integer32,
    wwpContainmentMulticastLowMark          Integer32,
    wwpContainmentMulticastTrapsEnable      TruthValue,
    wwpContainmentMulticastState            INTEGER
 }

 wwpContainmentMulticastPortId OBJECT-TYPE
    SYNTAX       INTEGER (1..65535)
    MAX-ACCESS   read-only
    STATUS       current
    DESCRIPTION
	    "The Id of the port for which this entry contains the containment
	    settings.  This value corresponds to the same portId for this port
	    defined in the object wwpPortStatsPortId as defined in the MIB
	    wwpPortStatsMIB."
      ::= { wwpContainmentMulticastEntry 1 }

 wwpContainmentMulticastAction  OBJECT-TYPE
     SYNTAX           INTEGER {
                        disable(1),
                        monitor(2),
                        throttle(3)
                      }
     MAX-ACCESS      read-write
     STATUS          current
     DESCRIPTION
       "This value defines the action that is associated
       with the multicast containment mechanism for this port.

       When this object contains the value of disable(1),
       then all multicast containment activity for this port
       is disabled.

       When this object contains the value of monitor(1),
       then the multicast containment mechanism will not
       inhibit packet forwarding on this port while the
       multicast containment mechanism is engaged. This
       setting is useful for monitoring SNMP traps that may
       be generated by the multicast containment mechanism.

       When this object contains the value of throttle(2),
       then the multicast containment mechanism will inhibit
       packet forwarding on this port while the multicast
       containment mechanism is engaged."
       DEFVAL { 1 }
       ::= { wwpContainmentMulticastEntry 2 }


 wwpContainmentMulticastHighMark  OBJECT-TYPE
     SYNTAX          Integer32(0..2147483647)
     MAX-ACCESS      read-write
     STATUS          current
     DESCRIPTION
	    "The value which must be reached or exceeded to trigger
	    the engagement of the multicast containment mechanism.

	    To prevent containment engagement lockup, the multicast
	    containment mechanism will not engage if the value of
	    this is less than or equal to the value specified in
	    wwpContainmentMulticastLowMark.

	    This value refers to the number of ingressing
	    frames-per-second."
       ::= { wwpContainmentMulticastEntry 3 }

 wwpContainmentMulticastLowMark  OBJECT-TYPE
     SYNTAX          Integer32(0..2147483647)
     MAX-ACCESS      read-write
     STATUS          current
     DESCRIPTION
        "The value which must be reached or preceded to release
        the engagement of the multicast containment mechanism.

	    This value refers to the number of ingressing
	    frames-per-second."
       ::= { wwpContainmentMulticastEntry 4 }

 wwpContainmentMulticastTrapsEnable  OBJECT-TYPE
     SYNTAX          TruthValue
     MAX-ACCESS      read-write
     STATUS          current
     DESCRIPTION
       "Enables or disables the traps associated with the
       containment mechanism for this port.  When
       set to true, a trap will be sent when the
       multicast containment mechanism becomes engaged
       and a trap will be sent when the multicast
       containment mechanism becomes disengaged. When
       set to false, no containment traps will be
       sent from the multicast containment mechanism
       for this port."
       DEFVAL { true }
       ::= { wwpContainmentMulticastEntry 5 }

 wwpContainmentMulticastState OBJECT-TYPE
     SYNTAX           INTEGER {
                        idle(1),
                        starting(2),
                        engaged(3),
                        stopping(4)
                      }
     MAX-ACCESS      read-only
     STATUS          current
     DESCRIPTION
       "This value indicates the present state of the
       multicast containment mechanism within the device.

       idle(1) - The multicast containment is presently
       disengaged.

       starting(2) - The multicast containment mechanism has
       determined that the conditions warrant the engagement
       of the multicast containment mechanism.  This is a
       momentary state which may exist during the transition
       from the idle state to the engaged state.

       engaged(3) - The multicast containment mechanism is
       currently engaged.  The action defined by
       wwpContainmentMulticastAction is presently in effect.

       stopping(4) - The multicast containment mechanism has
       determined that the conditions warrant the disengagement
       of the multicast containment mechanism.  This is a
       momentary state which may exist during the transition
       from the engaged state to the idle state."
       ::= { wwpContainmentMulticastEntry 6 }



 wwpContainmentNotification NOTIFICATION-TYPE
	OBJECTS	{
                wwpContainmentBroadcastState,
                wwpContainmentMulticastState
		}
	STATUS	current
	DESCRIPTION
		"A wwpContainmentNotification is sent when the
		wwpContainmentBroadcastState is changed or when the
		wwpContainmentMulticastState is changed."
	::= { wwpContainmentMIBNotifications 1 }

 END

 --
 -- WWP-CONTAINMENT-MIB
 --
