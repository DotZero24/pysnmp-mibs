--
 -- WWP-LEOS-OSPF-MIB.my
 --
 --

 WWP-LEOS-OSPF-MIB DEFINITIONS ::= BEGIN

 IMPORTS
   Unsigned32, MODULE-IDENTITY, OBJECT-TYPE, Counter32, Gauge32, Integer32, IpAddress
      FROM SNMPv2-SMI
   TEXTUAL-CONVENTION, TruthValue, RowStatus
      FROM SNMPv2-TC
   AreaID
      FROM OSPF-MIB
   wwpModulesLeos
	FROM WWP-SMI;


 wwpLeosOspfMIB MODULE-IDENTITY
	    LAST-UPDATED "200508050700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "This MIB module is for the Extension of the OSPF MIB for WWP Products"
	    REVISION    "200104031700Z"
	    DESCRIPTION
		    "Initial creation."
	    ::= { wwpModulesLeos 31 }

 --
 -- Textual conventions
 --

 OspfOperStatus ::= TEXTUAL-CONVENTION
    STATUS      current
    DESCRIPTION
       "The current operational state of an OSPF Protocol Manager entity."
    SYNTAX      INTEGER {
                  operStatusUp(1),       -- active
                  operStatusDown(2),     -- inactive
                  operStatusGoingUp(3),  -- activating
                  operStatusGoingDown(4),-- deactivating
                  operStatusActFailed(5) -- activation failed
                }

 --
 -- Node definitions
 --

 wwpLeosOspfMIBObjects          OBJECT IDENTIFIER ::= { wwpLeosOspfMIB 1 }
 wwpLeosOspfGeneralGroup        OBJECT IDENTIFIER ::= { wwpLeosOspfMIBObjects 1 }
 wwpLeosOspf                    OBJECT IDENTIFIER ::= { wwpLeosOspfMIBObjects 2 }

 wwpLeosOspfRFC1583Comp  OBJECT-TYPE
    SYNTAX       TruthValue
    MAX-ACCESS   read-write
    STATUS       current
    DESCRIPTION
       "Indicates metrics used to choose among multiple
       AS-external-LSAs.  When RFC1583Compatibility is set to
       TRUE, only cost will be used when choosing among
       multiple AS-external-LSAs advertising the same
       destination.  When RFC1583Compatibility is set to
       FALSE, preference will be driven first by type of
       path using cost only to break ties.

       In order to minimize the chance of routing loops, all OSPF
       routers in an OSPF routing domain should have
       RFC1583Compatibility set identically.  When there are routers
       present that have not been updated with the functionality
       specified in RFC2328 Section 16.4.1, all routers should
       have RFC1583Compatibility set to TRUE.  Otherwise, all
       routers should have RFC1583Compatibility set to FALSE,
       preventing all routing loops."
    REFERENCE
       "OSPF Version 2, Section 16.4.1 External path preferences"
    DEFVAL { false }
    ::= { wwpLeosOspfGeneralGroup 1 }

  wwpLeosOspfOperStatus OBJECT-TYPE
       SYNTAX       OspfOperStatus
       MAX-ACCESS   read-only
       STATUS       current
       DESCRIPTION
          "The current operational state of OSPF."
       ::= { wwpLeosOspfGeneralGroup 2 }


  wwpLeosOspfOpaqueLsaSupport  OBJECT-TYPE
       SYNTAX       TruthValue
       MAX-ACCESS   read-write
       STATUS       current
       DESCRIPTION
          "The router's support for Opaque LSA types.  This value cannot be
           changed when OSPF is active and operStatus is up."
       REFERENCE
          "The OSPF Opaque LSA Option"
       DEFVAL { true }
       ::= { wwpLeosOspfGeneralGroup 3 }

  wwpLeosOspfTrafficEngSupport OBJECT-TYPE
       SYNTAX       TruthValue
       MAX-ACCESS   read-only
       STATUS       current
       DESCRIPTION
          "The router's support for OSPF traffic engineering."
       DEFVAL { true }
       ::= { wwpLeosOspfGeneralGroup 4 }

  wwpLeosOspfExtOpLsaCount OBJECT-TYPE
       SYNTAX       Gauge32
       MAX-ACCESS   read-only
       STATUS       current
       DESCRIPTION
          "The number of type-11 LSAs in the external database."
       ::= { wwpLeosOspfGeneralGroup 5 }

  wwpLeosOspfExtOpLsaCksumSum OBJECT-TYPE
       SYNTAX       Integer32
       MAX-ACCESS   read-only
       STATUS       current
       DESCRIPTION
          "The 32 bit sum of LS checksums of all type-11 LSAs in the
          external Link State Database."
       ::= { wwpLeosOspfGeneralGroup 6 }

  wwpLeosOspfNumUpdPending OBJECT-TYPE
       SYNTAX       Unsigned32
       MAX-ACCESS   read-only
       STATUS       current
       DESCRIPTION
          "The number of updates that are pending addition to the Link State
          Database."
       ::= { wwpLeosOspfGeneralGroup 7 }

  wwpLeosOspfNumUpdMerged OBJECT-TYPE
       SYNTAX       Unsigned32
       MAX-ACCESS   read-only
       STATUS       current
       DESCRIPTION
          "The number of updates that have been merged into the Link State
          Database since the last routing calculation."
       ::= { wwpLeosOspfGeneralGroup 8 }

  wwpLeosOspfNumCksumsPending OBJECT-TYPE
       SYNTAX       Unsigned32
       MAX-ACCESS   read-only
       STATUS       current
       DESCRIPTION
          "The number of LSAs in the Link State Database which are now due to
          have their checksum checked."
       ::= { wwpLeosOspfGeneralGroup 9 }

  wwpLeosOspfCalcMaxDelay OBJECT-TYPE
       SYNTAX       Unsigned32
       UNITS        "milliseconds"
       MAX-ACCESS   read-write
       STATUS       current
       DESCRIPTION
          "The maximum delay before the Routing Table is
          recalculated following a change to the Link State
          Database.  (Recalculation is delayed to reduce the
          frequency of recalculations of the Routing Table).

          This parameter has units of milliseconds.  A value of
          0 indicates that a routing calculation will
          immediately follow an update to the database."
       DEFVAL { 5000 }
       ::= { wwpLeosOspfGeneralGroup 10 }

--      The OSPF Area Data Structure contains information
--      regarding the various areas. The interfaces and
--      virtual links are configured as part of these areas.
--      Area 0.0.0.0, by definition, is the Backbone Area


 wwpLeosOspfAreaTable OBJECT-TYPE
     SYNTAX   SEQUENCE OF WwpLeosOspfAreaEntry
     MAX-ACCESS   not-accessible
     STATUS   current
     DESCRIPTION
        "Information describing the configured  parame-
        ters  and cumulative statistics of the router's
        attached areas."
    REFERENCE
       "OSPF Version 2, Section 6  The Area Data Struc-
       ture"
   ::= { wwpLeosOspf 1 }


 wwpLeosOspfAreaEntry OBJECT-TYPE
     SYNTAX   WwpLeosOspfAreaEntry
     MAX-ACCESS   not-accessible
     STATUS   current
     DESCRIPTION
        "Information describing the configured  parame-
        ters  and  cumulative  statistics of one of the
        router's attached areas."
    INDEX { wwpLeosOspfAreaId }
    ::= { wwpLeosOspfAreaTable 1 }

 WwpLeosOspfAreaEntry ::=
   SEQUENCE {
       wwpLeosOspfAreaId                   AreaID,
       wwpLeosOspfAreaTransitCapability    TruthValue,
       wwpLeosOspfAreaRtrLsaCount          Gauge32,
       wwpLeosOspfAreaRtrLsaCksumSum       Integer32,
       wwpLeosOspfAreaNetLsaCount	   Gauge32,
       wwpLeosOspfAreaNetLsaCksumSum	   Integer32,
       wwpLeosOspfAreaSummLsaCount         Gauge32,
       wwpLeosOspfAreaSummLsaCksumSum	   Integer32,
       wwpLeosOspfAreaSummAsLsaCount	   Gauge32,
       wwpLeosOspfAreaSummAsLsaCksumSum    Integer32,
       wwpLeosOspfAreaNssaLsaCount	   Gauge32,
       wwpLeosOspfAreaNssaLsaCksumSum      Integer32,
       wwpLeosOspfAreaOpLsaCount	   Gauge32,
       wwpLeosOspfAreaOpLsaCksumSum	   Integer32
             }

  wwpLeosOspfAreaId OBJECT-TYPE
      SYNTAX   AreaID
      MAX-ACCESS   not-accessible
      STATUS   current
      DESCRIPTION
         "A 32-bit integer uniquely identifying an area.
         Area ID 0.0.0.0 is used for the OSPF backbone."
     REFERENCE
        "OSPF Version 2, Appendix C.2 Area parameters"
    ::= { wwpLeosOspfAreaEntry 1 }


 wwpLeosOspfAreaTransitCapability OBJECT-TYPE
      SYNTAX       TruthValue
      MAX-ACCESS   read-only
      STATUS       current
      DESCRIPTION
         "This parameter indicates whether the area can carry data
         traffic that neither originates nor terminates in the area
         itself.  This parameter is calculated when the area's shortest-path
         tree is built."
      DEFVAL { false }
      ::= { wwpLeosOspfAreaEntry 2 }

 wwpLeosOspfAreaRtrLsaCount OBJECT-TYPE
      SYNTAX       Gauge32
      MAX-ACCESS   read-only
      STATUS       current
      DESCRIPTION
         "The number of LSAs with LS type-1 in this area's Link State
         Database."
      ::= { wwpLeosOspfAreaEntry 3 }

 wwpLeosOspfAreaRtrLsaCksumSum OBJECT-TYPE
      SYNTAX       Integer32
      MAX-ACCESS   read-only
      STATUS       current
      DESCRIPTION
         "The 32 bit sum of LS checksums of all LSAs with LS type-1 in this
         area's Link State Database."
      ::= { wwpLeosOspfAreaEntry 4 }

 wwpLeosOspfAreaNetLsaCount OBJECT-TYPE
      SYNTAX       Gauge32
      MAX-ACCESS   read-only
      STATUS       current
      DESCRIPTION
         "The number of LSAs with LS type-2 in this area's Link State
         Database."
      ::= { wwpLeosOspfAreaEntry 5 }

 wwpLeosOspfAreaNetLsaCksumSum OBJECT-TYPE
      SYNTAX       Integer32
      MAX-ACCESS   read-only
      STATUS       current
      DESCRIPTION
         "The 32 bit sum of LS checksums of all LSAs with LS type-2 in this
         area's Link State Database."
      ::= { wwpLeosOspfAreaEntry 6 }

 wwpLeosOspfAreaSummLsaCount OBJECT-TYPE
      SYNTAX       Gauge32
      MAX-ACCESS   read-only
      STATUS       current
      DESCRIPTION
         "The number of LSAs with LS type-3 in this area's Link State
         Database."
      ::= { wwpLeosOspfAreaEntry 7 }

 wwpLeosOspfAreaSummLsaCksumSum OBJECT-TYPE
      SYNTAX       Integer32
      MAX-ACCESS   read-only
      STATUS       current
      DESCRIPTION
         "The 32 bit sum of LS checksums of all LSAs with LS type-3 in this
         area's Link State Database."
      ::= { wwpLeosOspfAreaEntry 8 }

 wwpLeosOspfAreaSummAsLsaCount OBJECT-TYPE
      SYNTAX       Gauge32
      MAX-ACCESS   read-only
      STATUS       current
      DESCRIPTION
         "The number of LSAs with LS type-4 in this area's Link State
         Database."
      ::= { wwpLeosOspfAreaEntry 9 }

 wwpLeosOspfAreaSummAsLsaCksumSum OBJECT-TYPE
      SYNTAX       Integer32
      MAX-ACCESS   read-only
      STATUS       current
      DESCRIPTION
         "The 32 bit sum of LS checksums of all LSAs with LS type-4 in this
         area's Link State Database."
      ::= { wwpLeosOspfAreaEntry 10 }

 wwpLeosOspfAreaNssaLsaCount OBJECT-TYPE
      SYNTAX       Gauge32
      MAX-ACCESS   read-only
      STATUS       current
      DESCRIPTION
         "The number of LSAs with LS type-7 in this area's Link State
          Database."
      ::= { wwpLeosOspfAreaEntry 11 }

 wwpLeosOspfAreaNssaLsaCksumSum OBJECT-TYPE
      SYNTAX       Integer32
      MAX-ACCESS   read-only
      STATUS       current
      DESCRIPTION
         "The 32 bit sum of LS checksums of all LSAs with LS type-7 in this
         area's Link State Database."
      ::= { wwpLeosOspfAreaEntry 12 }

 wwpLeosOspfAreaOpLsaCount OBJECT-TYPE
      SYNTAX       Gauge32
      MAX-ACCESS   read-only
      STATUS       current
      DESCRIPTION
         "The number of LSAs with LS type-10 in this area's Link State
         Database."
      ::= { wwpLeosOspfAreaEntry 13 }

 wwpLeosOspfAreaOpLsaCksumSum OBJECT-TYPE
      SYNTAX       Integer32
      MAX-ACCESS   read-only
      STATUS       current
      DESCRIPTION
         "The 32 bit sum of LS checksums of all LSAs with LS type-10 in this
         area's Link State Database."
       ::= { wwpLeosOspfAreaEntry 14 }

--  WWP OSPF Interface Table

--  The WWP OSPF Interface Table augments the OSPF Interface Table

 wwpLeosOspfIfTable OBJECT-TYPE
     SYNTAX   SEQUENCE OF WwpLeosOspfIfEntry
     MAX-ACCESS   not-accessible
     STATUS   current
     DESCRIPTION
        "The OSPF Interface Table describes the  inter-
        faces from the viewpoint of OSPF."
    REFERENCE
       "OSPF Version 2, Appendix C.3  Router  interface
       parameters"
   ::= { wwpLeosOspf 2 }


 wwpLeosOspfIfEntry OBJECT-TYPE
     SYNTAX   WwpLeosOspfIfEntry
     MAX-ACCESS   not-accessible
     STATUS   current
     DESCRIPTION
        "The OSPF Interface Entry describes one  inter-
        face from the viewpoint of OSPF."
    INDEX { wwpLeosOspfIfIpAddress, wwpLeosOspfAddressLessIf }
    ::= { wwpLeosOspfIfTable 1 }

 WwpLeosOspfIfEntry ::=
     SEQUENCE {
         wwpLeosOspfIfIpAddress                 IpAddress,
         wwpLeosOspfAddressLessIf               Integer32,
         wwpLeosOspfIfLsaCount                  Gauge32,
         wwpLeosOspfIfLsaCksumSum               Integer32,
         wwpLeosOspfIfOperStatus                OspfOperStatus,
         wwpLeosOspfIfNetMask                   IpAddress,
         wwpLeosOspfIfTransmitTimerDelay        INTEGER
         }

 wwpLeosOspfIfIpAddress OBJECT-TYPE
      SYNTAX   IpAddress
      MAX-ACCESS   not-accessible
      STATUS   current
      DESCRIPTION
         "The IP address of this OSPF interface."
     ::= { wwpLeosOspfIfEntry 1 }

 wwpLeosOspfAddressLessIf OBJECT-TYPE
      SYNTAX   Integer32
      MAX-ACCESS   not-accessible
      STATUS   current
      DESCRIPTION
         "For the purpose of easing  the  instancing  of
         addressed   and  addressless  interfaces;  This
         variable takes the value 0 on  interfaces  with
         IP  Addresses,  and  the corresponding value of
         ifIndex for interfaces having no IP Address."
     ::= { wwpLeosOspfIfEntry 2 }

 wwpLeosOspfIfLsaCount OBJECT-TYPE
      SYNTAX       Gauge32
      MAX-ACCESS   read-only
      STATUS       current
      DESCRIPTION
         "The total number of link-local link state advertisements
         in this interface's link-local link state database."
      ::= { wwpLeosOspfIfEntry 3 }

 wwpLeosOspfIfLsaCksumSum OBJECT-TYPE
      SYNTAX       Integer32
      MAX-ACCESS   read-only
      STATUS       current
      DESCRIPTION
         "The 32-bit unsigned sum of the link-state
         advertisements' LS checksums contained in this
         interface's link-local link state database.
         The sum can be used to determine if there has
         been a change in the interface's link state database,
         and to compare the interface link-state database of
         routers attached to the same subnet."
      ::= { wwpLeosOspfIfEntry 4 }

 wwpLeosOspfIfOperStatus OBJECT-TYPE
      SYNTAX       OspfOperStatus
      MAX-ACCESS   read-only
      STATUS       current
      DESCRIPTION
         "The current operational state of this interface."
      ::= { wwpLeosOspfIfEntry 5 }

 wwpLeosOspfIfNetMask OBJECT-TYPE
      SYNTAX       IpAddress
      MAX-ACCESS   read-only
      STATUS       current
      DESCRIPTION
        "The subnet mask associated with the IP address of this entry.  The
        value of the mask is an IP address with all the network bits set to 1
        and all the hosts bits set to 0."
      ::= { wwpLeosOspfIfEntry 6 }

  wwpLeosOspfIfTransmitTimerDelay OBJECT-TYPE
       SYNTAX       INTEGER (1..429496999)
       UNITS        "milliseconds"
       MAX-ACCESS   read-write
       STATUS       current
       DESCRIPTION
          "The time this interface will delay a LSU packet, in order to
          add more LSAs to the packet before sending.  Setting this
          correctly can reduce the network traffic.  This is configurable
          on a per-interface basis."
       DEFVAL { 100 }
       ::= { wwpLeosOspfIfEntry 7 }

 END

 --
 -- WWP-LEOS-OSPF-MIB
 --
