--
 -- WWP-SYSLOG-COLLECTOR-MIB.my
 --

 WWP-SYSLOG-COLLECTOR-MIB DEFINITIONS ::= BEGIN

 IMPORTS
	TEXTUAL-CONVENTION FROM SNMPv2-TC
    IpAddress, Integer32, OBJECT-TYPE, MODULE-IDENTITY
	FROM SNMPv2-SMI
    RowStatus, TruthValue
	FROM SNMPv2-TC
    wwpModules
	FROM WWP-SMI;

 wwpSyslogCollectorMIB MODULE-IDENTITY
    LAST-UPDATED "200301211012Z"
    ORGANIZATION
	     "   World Wide Packets Inc"
    CONTACT-INFO
	     "   Mib Meister
	         Postal: World Wide Packets
		 P.O. Box 950
		 Veradale, WA 99037
		 USA
		 Phone:  +1 509 242 9000
		 Email:  mib.meister@worldwidepackets.com"

     DESCRIPTION
	     "A MIB module to manage syslog collectors on the
	     LEOS based WWP products."
     REVISION    "200301211012Z"
     DESCRIPTION
	     "Initial Creation"
     ::= { wwpModules 46 }


 -- -------------------------------------------------------------
 -- Textual Conventions
 -- -------------------------------------------------------------

 SyslogFacility  ::=  TEXTUAL-CONVENTION
     STATUS  current
     DESCRIPTION
         "This textual convention enumerates the facilities
         that originate syslog messages.

         The value noMap(24) indicates that the appropriate
         facility will be provided by the individual applications
         on the managed entity.  If this option is not available
         on a particular entity attempt set the facillity to this
         value will fail with an error-status of wrongValue."
     SYNTAX  INTEGER {
                       kernel          (0), -- kernel messages
                       user            (1), -- user-level messages
                       mail            (2), -- mail system
                       daemon          (3), -- system daemons
                       auth            (4), -- authorization messages
                       syslog          (5), -- messages generated by syslogd
                       lpr             (6), -- line printer subsystem
                       news            (7), -- network news subsystem
                       uucp            (8), -- UUCP subsystem
                       cron            (9), -- clock daemon
                       authPriv        (10),-- authorization messages
                                            --    (private)
                       ftp             (11),-- ftp daemon
                       ntp             (12),-- NTP subsystem
                       security        (13),-- security subsystems
                                            --    (firewalling, etc.)
                       console         (14),-- /dev/console output
                       local0          (16),
                       local1          (17),
                       local2          (18),
                       local3          (19),
                       local4          (20),
                       local5          (21),
                       local6          (22),
                       local7          (23),
                       noMap           (99)
                     }


 SyslogSeverity  ::=  TEXTUAL-CONVENTION
     STATUS  current
     DESCRIPTION
         "This textual convention enumerates the severity levels
          of syslog messages.  The syslog protocol uses the values
          0 (emergency), to 7 (debug)."
     SYNTAX  INTEGER {
                       emergency       (0),  -- system is unusable
                       alert           (1),  -- action must be taken
                                             --          immediately
                       critical        (2),  -- critical conditions
                       error           (3),  -- error conditions
                       warning         (4),  -- warning conditions
                       notice          (5),  -- normal but significant
                                             -- condition
                       info            (6),  -- informational
                       debug           (7),  -- debug-level messages
                       other           (99)  -- None of the above
                     }

 --
 -- Node definitions
 --

 wwpSyslogCollMIBObjects OBJECT IDENTIFIER ::= { wwpSyslogCollectorMIB 1 }

 wwpSyslogSystem  OBJECT IDENTIFIER ::= { wwpSyslogCollMIBObjects 1 }

 wwpSyslogColl    OBJECT IDENTIFIER ::= { wwpSyslogCollMIBObjects 2 }

 -- Notifications

 wwpSyslogCollMIBNotificationPrefix  OBJECT IDENTIFIER ::= { wwpSyslogCollectorMIB 2 }
 wwpSyslogCollMIBNotifications       OBJECT IDENTIFIER ::=
                       { wwpSyslogCollMIBNotificationPrefix 0 }

 -- Conformance information

 wwpSyslogCollMIBConformance OBJECT IDENTIFIER ::= { wwpSyslogCollectorMIB 3 }
 wwpSyslogCollMIBCompliances OBJECT IDENTIFIER ::= { wwpSyslogCollMIBConformance 1 }
 wwpSyslogCollMIBGroups      OBJECT IDENTIFIER ::= { wwpSyslogCollMIBConformance 2 }

 -- The system wide parameters

 wwpSyslogEnable OBJECT-TYPE
     SYNTAX      TruthValue
     MAX-ACCESS  read-write
     STATUS      current
     DESCRIPTION
             "Specifies whether or not the syslog client is enabled.
             This is the system wide parameter and will overwrite
	     any collector specific managed object to enable
	     or disable the syslog client."
     DEFVAL { true }
     ::= { wwpSyslogSystem 1 }

 -- -------------------------------------------------------------
 -- wwpSyslogCollector Table
 -- -------------------------------------------------------------
 -- Each row in this table defines a destination to which the
 -- message will be forwarded

 wwpSyslogCollectorTable OBJECT-TYPE
     SYNTAX      SEQUENCE OF WwpSyslogCollectorEntry
     MAX-ACCESS  not-accessible
     STATUS      current
     DESCRIPTION
         "A table containing Syslog collector information."
     ::= { wwpSyslogColl 1 }

 wwpSyslogCollectorEntry OBJECT-TYPE
     SYNTAX      WwpSyslogCollectorEntry
     MAX-ACCESS  not-accessible
     STATUS      current
     DESCRIPTION
         "Defines the information pertaining to a syslog collector
          to which a syslog messages will be relayed.

          Entries within this table with an access level of read-
          create MUST be considered non-volatile and MUST be
	  maintained across entity resets."
     INDEX  { wwpSyslogCollectorAddr }
     ::= { wwpSyslogCollectorTable 1 }


 WwpSyslogCollectorEntry ::=
     SEQUENCE {
         wwpSyslogCollectorAddr
              IpAddress,
         wwpSyslogCollectorUDPPort
              Integer32,
         wwpSyslogCollectorFacility
              SyslogFacility,
         wwpSyslogCollectorMinSeverity
              SyslogSeverity,
	 wwpSyslogCollectorMaxSeverity
              SyslogSeverity,
         wwpSyslogCollectorStatus
              RowStatus
     }

 wwpSyslogCollectorAddr OBJECT-TYPE
     SYNTAX      IpAddress
     MAX-ACCESS  read-only
     STATUS      current
     DESCRIPTION
           "The Ip address for the Syslog message collector."
     ::= { wwpSyslogCollectorEntry 1 }


 wwpSyslogCollectorUDPPort OBJECT-TYPE
     SYNTAX      Integer32 (1..65535)
     MAX-ACCESS  read-create
     STATUS      current
     DESCRIPTION
         "The port number on the destination to which the
          syslog message will be forwarded over the udp
	  transport."
     DEFVAL   { 514 }
     ::= { wwpSyslogCollectorEntry 2 }


 wwpSyslogCollectorFacility OBJECT-TYPE
     SYNTAX      SyslogFacility
     MAX-ACCESS  read-create
     STATUS      current
     DESCRIPTION
         "The syslog facility code that will added to messages forwarded
          to this collector.
         "
     DEFVAL   { daemon }
     ::= { wwpSyslogCollectorEntry 3 }

 wwpSyslogCollectorMinSeverity OBJECT-TYPE
     SYNTAX      SyslogSeverity
     MAX-ACCESS  read-create
     STATUS      current
     DESCRIPTION
          "Any syslog message with a severity less than the severity
	  specified by this object will be ignored by the collector. note:
	  serverity level numeric values increase as their
	  severity decreases, e.g. error(3) is more severe
	  than debug(7)."
     DEFVAL   { error }
     ::= { wwpSyslogCollectorEntry 4 }

 wwpSyslogCollectorMaxSeverity OBJECT-TYPE
     SYNTAX      SyslogSeverity
     MAX-ACCESS  read-create
     STATUS      current
     DESCRIPTION
          "Any syslog message with a severity greater than the severity
	  specified by this object will be ignored by the collector. note:
	  serverity level numeric values increase as their severity
	  decreases, e.g. error(3) is more severe than debug(7)."
     DEFVAL   { emergency }
     ::= { wwpSyslogCollectorEntry 5 }

 wwpSyslogCollectorStatus OBJECT-TYPE
     SYNTAX      RowStatus
     MAX-ACCESS  read-create
     STATUS      current
     DESCRIPTION
         "This object is used to create and delete rows in the
          wwpSyslogCollectorTable. To create a new row the
	  management station must set the object to 'CreateAndGo'.
	  The collector can be disabled by setting this object
	  to 'notInService'.
         "
     ::= { wwpSyslogCollectorEntry 6 }

  END

 --
 -- WWP-SYSLOG-COLLECTOR-MIB.my
 --
