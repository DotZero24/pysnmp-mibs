--
 -- WWP-SYSTEM-MIB.my
 --
 -- NOTE WELL
 -- Starting from LE2X 3.5, the bootp will be replaced by
 -- the dhcp, hence the object mentioned under wwpSystemBootp
 -- are deprecated. They have been replaced with
 -- objects defined in WWP-DHCP-CLIENT-MIB.my .
 -- Management Applications should no longer be
 -- examining the objects defined under the wwpSystemBootp
 --
 -- NOTE WELL

 WWP-SYSTEM-MIB DEFINITIONS ::= BEGIN

 IMPORTS
   IpAddress, Integer32, Unsigned32, OBJECT-TYPE, MODULE-IDENTITY
	    FROM SNMPv2-SMI
   DisplayString, TruthValue, MacAddress, DateAndTime, TEXTUAL-CONVENTION
	    FROM SNMPv2-TC
   wwpModules
	    FROM WWP-SMI;


 wwpSystemMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP System specific information. This MIB provide
                    additional information to whatever is provided by the standard system group."
	    REVISION     "200303110000Z"  -- 11th March. 2003
	    DESCRIPTION
		    "The debug group is added."
	    REVISION    "200104031700Z"
	    DESCRIPTION
		    "Initial creation."
	    ::= { wwpModules 2 }

 --
 -- Node definitions
 --

 wwpSystemMIBObjects OBJECT IDENTIFIER ::= { wwpSystemMIB 1 }

 -- System Clock
 --
 wwpSystemClock OBJECT IDENTIFIER ::= { wwpSystemMIBObjects 1 }

 --
 -- System Bootp
 --
 wwpSystemBootp OBJECT IDENTIFIER ::= { wwpSystemMIBObjects 2 }

 --
 -- System Attributes
 --
 wwpSystemAttr OBJECT IDENTIFIER ::= { wwpSystemMIBObjects 3 }

 --
 -- Cfg Group
 --
 wwpSystemCfg OBJECT IDENTIFIER ::= { wwpSystemMIBObjects 4 }


 --
 -- Debug Group
 --
 wwpSystemDebug OBJECT IDENTIFIER ::= { wwpSystemMIBObjects 5 }


 -- Notifications

 wwpSystemMIBNotificationPrefix  OBJECT IDENTIFIER ::= { wwpSystemMIB 2 }
 wwpSystemMIBNotifications       OBJECT IDENTIFIER ::=
                       { wwpSystemMIBNotificationPrefix 0 }

 -- Conformance information

 wwpSystemMIBConformance OBJECT IDENTIFIER ::= { wwpSystemMIB 3 }
 wwpSystemMIBCompliances OBJECT IDENTIFIER ::= { wwpSystemMIBConformance 1 }
 wwpSystemMIBGroups      OBJECT IDENTIFIER ::= { wwpSystemMIBConformance 2 }


 wwpSysClockDateTime    OBJECT-TYPE
     SYNTAX             DateAndTime
     MAX-ACCESS         read-write
     STATUS             current
     DESCRIPTION
	     "The current system date and time of box.

	      There are no privisions for local time or
	      daylight savings.  All times use the 24 hr clock
	      and are UTC.

	      Because device time is UTC, only first 7 bytes of
	      DateAndTime data are returned, per rfc1903."
      ::= { wwpSystemClock 1 }

 wwpSysClockTimeOffset OBJECT-TYPE
      SYNTAX        Integer32
      MAX-ACCESS    read-write
      STATUS        current
      DESCRIPTION
          "Value used in conjunction with the universal
          coordinated time (UTC) during the creation of
          caller ID messages.  The value of this object
          can also be modified by the DHCP using the
          Time Offset Option."
      DEFVAL { 0 }
      ::= { wwpSystemClock 2 }

 wwpSystemBootpMsgFreq OBJECT-TYPE
      SYNTAX        Unsigned32 (0..2147483647)
      UNITS         "in seconds"
      MAX-ACCESS    read-write
      STATUS        deprecated
      DESCRIPTION
	      "Defines how frequently (in seconds) that bootp
	      messages are sent to the host."
      DEFVAL { 12 }
      ::= { wwpSystemBootp 1 }

 wwpSystemStartMacAddr OBJECT-TYPE
     SYNTAX       MacAddress
     MAX-ACCESS   read-only
     STATUS       current
     DESCRIPTION
	     "Base MAC address for the device, from which all
 	      other mac addresses are derived."
     ::= { wwpSystemAttr 1 }

 wwpSystemDefaultGateway OBJECT-TYPE
     SYNTAX      IpAddress
     MAX-ACCESS  read-write
     STATUS      current
     DESCRIPTION
	     "Default gateway IP address."
     ::= { wwpSystemAttr 2 }

 wwpSystemTftpServer OBJECT-TYPE
      SYNTAX      IpAddress
      MAX-ACCESS  read-write
      STATUS      current
      DESCRIPTION
	      "Has the TFTP Server host name assigned by the bootp
	      server, and later used for subsequent bootp requests."
      ::= { wwpSystemAttr 3 }

 wwpSystemBootFile OBJECT-TYPE
      SYNTAX      DisplayString
      MAX-ACCESS  read-write
      STATUS      current
      DESCRIPTION
	      "Name of the dhcp cmd file for the system."
      ::= { wwpSystemAttr 4 }

 wwpSystemInterfaceHostName OBJECT-TYPE
      SYNTAX      DisplayString
      MAX-ACCESS  read-write
      STATUS      current
      DESCRIPTION
	      "Host name for vmi or smi interface."
      ::= { wwpSystemAttr 5 }

 wwpSystemCfgControl OBJECT-TYPE
      SYNTAX          INTEGER {
                           none(0),
			   save(1),
			   updatePasswords(2),
			   updateSnmpCfg(3),
			   mfgDefaultCfg(4)
		       }
      MAX-ACCESS       read-write
      STATUS           current
      DESCRIPTION
	      "Controls configuration options on the device.
              The current options are:
	      save:
		  to make the configuration changes made
		  using SNMP persistent across a reboot.

	      updatePasswords:
		  to update the current password file with
		  the new password file.  The new passwords
		  will become active immediately.

	      updateSnmpCfg:
		  to update the current snmp configuration
		  data. The new configuration will become
		  active immediately.

	      mfgDefaultCfg:
		   Set system configuration to factory defaults.
		   Note: this will wipe out all of the current
		   configuration including Password and VLAN
		   information.

             If the system doesn't support any of these control
             configuration option, it should return error while
             trying to set this object to the specific option.

             A read on this object should return none(0)."
       ::= { wwpSystemCfg 1 }

 wwpSystemCfgFilepath OBJECT-TYPE
      SYNTAX        DisplayString
      MAX-ACCESS    read-only
      STATUS        current
      DESCRIPTION
	      "Returns the path for configuration related files."
      ::= { wwpSystemCfg 2 }


 wwpSystemConsolePortEnable OBJECT-TYPE
      SYNTAX        TruthValue
      MAX-ACCESS    read-write
      STATUS        current
      DESCRIPTION
	      "Setting this object to 'true' will enable the
	      console port."
      DEFVAL { false }
      ::= { wwpSystemDebug 1 }


 END

 --
 -- WWP-SYSTEM-MIB.my
 --
