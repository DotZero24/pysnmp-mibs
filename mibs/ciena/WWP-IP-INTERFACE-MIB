--
 -- WWP-IP-INTERFACE-MIB.my
 --
 --

 WWP-IP-INTERFACE-MIB DEFINITIONS ::= BEGIN

 IMPORTS
   NOTIFICATION-TYPE, IpAddress, Integer32, Unsigned32, OBJECT-TYPE, MODULE-IDENTITY
	    FROM SNMPv2-SMI
   DisplayString, MacAddress, DateAndTime, TruthValue, TEXTUAL-CONVENTION
	    FROM SNMPv2-TC
   wwpModules
	    FROM WWP-SMI;


 wwpIpInterfaceMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP IpInterface Ip interfaces config. This MIB provide
                    additional configuration to whatever is provided by the standard ip group."
            REVISION     "200305020000Z"  -- 2nd May. 2003
	    DESCRIPTION
		    "A new object for mgmt packet priority is added."
	    REVISION    "200104031700Z"
	    DESCRIPTION
		    "Initial creation."
	    ::= { wwpModules 17 }

 VlanId ::= TEXTUAL-CONVENTION
    STATUS      current
    DESCRIPTION
        "A 12-bit VLAN ID used in the VLAN Tag header."
    SYNTAX      INTEGER (1..4094)

 --
 -- Node definitions
 --

 wwpIpInterfaceMIBObjects OBJECT IDENTIFIER ::= { wwpIpInterfaceMIB 1 }


 --
 -- IP INterface Node
 --
 wwpIpInterface OBJECT IDENTIFIER ::= { wwpIpInterfaceMIBObjects 1 }


 -- Notifications

 wwpIpInterfaceMIBNotificationPrefix  OBJECT IDENTIFIER ::= { wwpIpInterfaceMIB 2 }
 wwpIpInterfaceMIBNotifications       OBJECT IDENTIFIER ::=
                       { wwpIpInterfaceMIBNotificationPrefix 0 }

 -- Conformance information

 wwpIpInterfaceMIBConformance OBJECT IDENTIFIER ::= { wwpIpInterfaceMIB 3 }
 wwpIpInterfaceMIBCompliances OBJECT IDENTIFIER ::= { wwpIpInterfaceMIBConformance 1 }
 wwpIpInterfaceMIBGroups      OBJECT IDENTIFIER ::= { wwpIpInterfaceMIBConformance 2 }


 wwpIpInterfaceTable OBJECT-TYPE
     SYNTAX SEQUENCE OF WwpIpInterfaceEntry
     MAX-ACCESS   not-accessible
     STATUS       current
     DESCRIPTION
	     "Table of IP addresses and associated subnet mask."
     ::= { wwpIpInterface 1 }

 wwpIpInterfaceEntry OBJECT-TYPE
     SYNTAX     WwpIpInterfaceEntry
     MAX-ACCESS not-accessible
     STATUS     current
     DESCRIPTION
	     "Interface IP and subnet mask entry.
	     These interfaces are used to cause the switch CPU to
	     become involved witht he IP traffic. By default, a
	     minimum of two interfaces must always exist, one for
	     the local mgt interface, one for the remote mgt
	     interface, and one or more for voice over IP."
     INDEX { wwpIpInterfaceIndex }
	    ::= { wwpIpInterfaceTable 1 }

 WwpIpInterfaceEntry ::=  SEQUENCE {
      wwpIpInterfaceIndex       Integer32,
      wwpIpInterfaceName        DisplayString,
      wwpIpInterfaceIpAddr      IpAddress,
      wwpIpInterfaceSubnet      IpAddress,
      wwpIpInterfaceIfIndexXref INTEGER
 }

 wwpIpInterfaceIndex OBJECT-TYPE
      SYNTAX Integer32 (1..4096)
      MAX-ACCESS       read-only
      STATUS           current
      DESCRIPTION
	      "Unique index into the table."
      ::= { wwpIpInterfaceEntry 1 }

 wwpIpInterfaceName OBJECT-TYPE
     SYNTAX      DisplayString (SIZE (0..32))
     MAX-ACCESS  read-only
     STATUS      current
     DESCRIPTION
	     "The friendly name for the IP interface."
     ::= { wwpIpInterfaceEntry 2 }

 wwpIpInterfaceIpAddr OBJECT-TYPE
     SYNTAX       IpAddress
     MAX-ACCESS   read-write
     STATUS       current
     DESCRIPTION
	     "IP address associated with this interface. "
     ::= { wwpIpInterfaceEntry 3 }

 wwpIpInterfaceSubnet OBJECT-TYPE
     SYNTAX       IpAddress
     MAX-ACCESS   read-write
     STATUS       current
     DESCRIPTION
	     "The subnet mask associated with this ip address/interface."
     ::= { wwpIpInterfaceEntry 4 }


 wwpIpInterfaceIfIndexXref OBJECT-TYPE
     SYNTAX       INTEGER (1..4096)
     MAX-ACCESS   read-only
     STATUS       current
     DESCRIPTION
	     "Cross reference to MIB-2 Interfaces ifIndex."
     ::= { wwpIpInterfaceEntry 5 }

 wwpIpExtInterfaceTable OBJECT-TYPE
    SYNTAX      SEQUENCE OF WwpIpExtInterfaceEntry
    MAX-ACCESS  not-accessible
    STATUS      current
    DESCRIPTION
        "A table that contains Interface Specific
         information maintained by each interface."
    ::= { wwpIpInterface 2 }

 wwpIpExtInterfaceEntry OBJECT-TYPE
    SYNTAX      WwpIpExtInterfaceEntry
    MAX-ACCESS  not-accessible
    STATUS      current
    DESCRIPTION
        "A list of interfaces additional config parameters
        maintained by each interface."
    AUGMENTS    { wwpIpInterfaceEntry }
    ::= { wwpIpExtInterfaceTable 1 }

 WwpIpExtInterfaceEntry ::=
    SEQUENCE {
        wwpIpInterfaceEnable             TruthValue,
        wwpIpInterfaceVlanId             VlanId,
        wwpIpInterfaceMgmtPktPriority    INTEGER
    }

 wwpIpInterfaceEnable  OBJECT-TYPE
    SYNTAX      TruthValue
    MAX-ACCESS  read-write
    STATUS      current
    DESCRIPTION
        "The status of each interface. A value of true(1) indicates
        that this interface is enabled and a value of
        false(2) indicates that this interface is disabled.
        The device shouldn't allow the Management Station to disable
        all the interfaces available on the box."
    ::= { wwpIpExtInterfaceEntry 1 }

 wwpIpInterfaceVlanId  OBJECT-TYPE
    SYNTAX      VlanId
    MAX-ACCESS  read-write
    STATUS      current
    DESCRIPTION
        "The vlanId associated with this IP interface. The vlan indicated by
        wwpIpInterfaceVlanId should exist in the Vlan Table. If an interface
        has no vlan assocaited, then any read on this object should return
        'noSuchInstance'."
    ::= { wwpIpExtInterfaceEntry 2 }

 wwpIpInterfaceMgmtPktPriority  OBJECT-TYPE
    SYNTAX      INTEGER (0..7)
    MAX-ACCESS  read-write
    STATUS      current
    DESCRIPTION
        "The 802.1p Priority value for the mgmt traffic on this interface."
    ::= { wwpIpExtInterfaceEntry 3 }

 wwpIpInterfaceAddrNotifEnabled OBJECT-TYPE
     SYNTAX      TruthValue
     MAX-ACCESS  read-write
     STATUS      current
     DESCRIPTION
             "This variable  indicates  whether  the  system
             generates the wwpIpInterfaceAddrChgNotification.
             A false value prevents this notifications
             from being generated by this system."
    DEFVAL { true }
    ::= { wwpIpInterface 3 }

 wwpIpInterfaceAddrChgNotification NOTIFICATION-TYPE
	OBJECTS	{
	           wwpIpInterfaceName,
		   wwpIpInterfaceIpAddr,
		   wwpIpInterfaceSubnet
                }
	STATUS	current
	DESCRIPTION
		"A wwpIpInterfaceAddrChgNotification is sent whenever the
		ip address of an interface changes."
	::= { wwpIpInterfaceMIBNotifications 1 }

 END
