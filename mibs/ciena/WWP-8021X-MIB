--
-- WWP-8021X-MIB.my
-- MIB generated by MG-SOFT Visual MIB Builder Version 6.0  Build 88
-- Sunday, August 28, 2005 at 19:49:14
--

	WWP-8021X-MIB DEFINITIONS ::= BEGIN

		IMPORTS
			OBJECT-GROUP, NOTIFICATION-GROUP
				FROM SNMPv2-CONF
			IpAddress, Integer32, OBJECT-TYPE, MODULE-IDENTITY
				FROM SNMPv2-SMI
			RowStatus FROM SNMPv2-TC
			wwpModules
				FROM WWP-SMI;


		-- 1.3.6.1.4.1.6141.2.401
		wwp8021xMibModule MODULE-IDENTITY
			LAST-UPDATED "200508281935Z"		-- August 28, 2005 at 19:35 GMT
			ORGANIZATION
				"World Wide Packets, Inc"
			CONTACT-INFO
				"   Mib Meister
		  		Postal: World Wide Packets
				P.O. Box 950
				Veradale, WA 99037
				USA
		 		Phone:  +1 509 242 9000
				Email:  mib.meister@worldwidepackets.com"
			DESCRIPTION
				"Description."
			::= { wwpModules 401 }



--
-- Node definitions
--

		-- 1.3.6.1.4.1.6141.2.401.1
		wwp8021xMIB OBJECT IDENTIFIER ::= { wwp8021xMibModule 1 }


		-- 1.3.6.1.4.1.6141.2.401.1.1
		wwp8021xConf OBJECT IDENTIFIER ::= { wwp8021xMIB 1 }


		-- 1.3.6.1.4.1.6141.2.401.1.1.1
		wwp8021xGroups OBJECT IDENTIFIER ::= { wwp8021xConf 1 }


		-- 1.3.6.1.4.1.6141.2.401.1.1.1.1
	--	wwp8021xObjectGroup OBJECT-GROUP
	--		OBJECTS { object1 }
	--		STATUS current
	--		DESCRIPTION
	--			"Description."
	--		::= { wwp8021xGroups 1 }


		-- 1.3.6.1.4.1.6141.2.401.1.1.1.2
	--	wwp8021xNotificationGroup NOTIFICATION-GROUP
	--		NOTIFICATIONS { notification1 }
	--		STATUS current
	--		DESCRIPTION
	--			"Description."
	--		::= { wwp8021xGroups 2 }


		-- 1.3.6.1.4.1.6141.2.401.1.1.2
		wwp8021xCompls OBJECT IDENTIFIER ::= { wwp8021xConf 2 }


		-- 1.3.6.1.4.1.6141.2.401.1.2
		wwp8021xObjs OBJECT IDENTIFIER ::= { wwp8021xMIB 2 }

		-- 1.3.6.1.4.1.6141.2.401.1.2.1
		wwp8021xPortTable OBJECT-TYPE
			SYNTAX SEQUENCE OF Wwp8021xPortEntry
			MAX-ACCESS not-accessible
			STATUS current
			DESCRIPTION
				"Table with an entry for every port on the switch"
			::= { wwp8021xObjs 1 }


		-- 1.3.6.1.4.1.6141.2.401.1.2.1.1
		wwp8021xPortEntry OBJECT-TYPE
			SYNTAX Wwp8021xPortEntry
			MAX-ACCESS not-accessible
			STATUS current
			DESCRIPTION
				"Description."
			INDEX { wwp8021xPort }
			::= { wwp8021xPortTable 1 }


		Wwp8021xPortEntry ::=
			SEQUENCE {
				wwp8021xPort
					INTEGER,
				wwp8021xRole
					INTEGER
			 }

		-- 1.3.6.1.4.1.6141.2.401.1.2.1.1.1
		wwp8021xPort OBJECT-TYPE
			SYNTAX INTEGER (1..1000)
			MAX-ACCESS read-only
			STATUS current
			DESCRIPTION
				"Switch Ethernet Port"
			::= { wwp8021xPortEntry 1 }


		-- 1.3.6.1.4.1.6141.2.401.1.2.1.1.2
		wwp8021xRole OBJECT-TYPE
			SYNTAX INTEGER
				{
				none(1),
				supplicant(2),
				authenticator(3),
				both(4)
				}
			MAX-ACCESS read-write
			STATUS current
			DESCRIPTION
				"802.1x role of the Port."
			::= { wwp8021xPortEntry 2 }



		-- Radius configuration
		-- 1.3.6.1.4.1.6141.2.401.1.2.2
		wwp8021xRadiusClient OBJECT IDENTIFIER ::= { wwp8021xObjs 2 }

		-- 1.3.6.1.4.1.6141.2.401.1.2.2.1
		wwp8021xRadiusClientTimeout OBJECT-TYPE
     		SYNTAX       Integer32 (1..30)
     		UNITS        "seconds"
     		MAX-ACCESS   read-write
     		STATUS       current
     		DESCRIPTION
	     		"This is the time in seconds between retransmissions
	      		to the RADIUS server."
     		DEFVAL { 1 }
     		::= { wwp8021xRadiusClient 1 }

	-- 1.3.6.1.4.1.6141.2.401.1.2.2.2
 		wwp8021xRadiusClientRetries   OBJECT-TYPE
     		SYNTAX         Integer32 (1..3)
     		MAX-ACCESS     read-write
     		STATUS         current
     		DESCRIPTION
		     	"Indicates the number of times the RADIUS server should be
		     	tried before giving up on the server."
	     	DEFVAL { 3 }
	     ::= { wwp8021xRadiusClient 2 }

	-- 1.3.6.1.4.1.6141.2.401.1.2.2.3
		wwp8021xRadiusDeadTime OBJECT-TYPE
     		SYNTAX       Integer32 (0..2000)
     		UNITS        "minutes"
     		MAX-ACCESS   read-write
     		STATUS       current
     		DESCRIPTION
	     		"Length of time in minutes during which a RADIUS server is
	     		skipped over by transaction requests.."
     		DEFVAL { 60 }
     		::= { wwp8021xRadiusClient 3 }

	-- 1.3.6.1.4.1.6141.2.401.1.2.2.4
		 wwp8021xRadiusServerTable OBJECT-TYPE
		     SYNTAX         SEQUENCE OF Wwp8021xRadiusServerEntry
		     MAX-ACCESS     not-accessible
		     STATUS         current
		     DESCRIPTION
			     "Lists the possible RADIUS servers."
		     ::= { wwp8021xRadiusClient 4 }

	-- 1.3.6.1.4.1.6141.2.401.1.2.2.4.1
		 wwp8021xRadiusServerEntry OBJECT-TYPE
		     SYNTAX       Wwp8021xRadiusServerEntry
		     MAX-ACCESS   not-accessible
		     STATUS       current
		     DESCRIPTION
			     "Radius server entry."
		     INDEX { wwp8021xRadiusServerId }
		     ::= { wwp8021xRadiusServerTable 1 }

		 Wwp8021xRadiusServerEntry ::= SEQUENCE {
		     wwp8021xRadiusServerId                              Integer32,
		     wwp8021xRadiusServerIpAddr	                          IpAddress,
		     wwp8021xRadiusServerAuthPort                        Integer32,
		     wwp8021xRadiusServerAuthKey                         OCTET STRING,
		     wwp8021xRadiusServerStatus                          RowStatus
		 }

	-- 1.3.6.1.4.1.6141.2.401.1.2.2.4.1.1
		 wwp8021xRadiusServerId  OBJECT-TYPE
		     SYNTAX       Integer32(1..2147483647)
		     MAX-ACCESS   read-only
		     STATUS       current
		     DESCRIPTION
			     "Index to the Radius Server Entry. The radius Servers are
		             polled according to their ServerIds. If the ServerId 1
		             doesn't respond, then it tries for the next and hence on."
		     ::= { wwp8021xRadiusServerEntry 1 }

	-- 1.3.6.1.4.1.6141.2.401.1.2.2.4.1.2
		 wwp8021xRadiusServerIpAddr OBJECT-TYPE
		     SYNTAX       IpAddress
		     MAX-ACCESS   read-create
		     STATUS       current
		     DESCRIPTION
			     "IP Address of the RADIUS server."
		     ::= { wwp8021xRadiusServerEntry 2 }

	-- 1.3.6.1.4.1.6141.2.401.1.2.2.4.1.3
		 wwp8021xRadiusServerAuthPort OBJECT-TYPE
		      SYNTAX      Integer32 (1..65535)
		      MAX-ACCESS  read-create
		      STATUS      current
		      DESCRIPTION
			      "The destination UDP port number to which RADIUS
			      messages should be sent.  The RADIUS server will not be
			      used for authentication if this port number is 0."
		      DEFVAL { 1812 }
		      ::= { wwp8021xRadiusServerEntry 3 }

	-- 1.3.6.1.4.1.6141.2.401.1.2.2.4.4
		 wwp8021xRadiusServerAuthKey  OBJECT-TYPE
		      SYNTAX OCTET STRING (SIZE (8..127))
		      MAX-ACCESS read-create
		      STATUS current
		      DESCRIPTION
		            "The Auth Key to be used for Radius Servers.
             Retrieving the value of this object via SNMP will
             return an empty string for security reasons"
		      ::= { wwp8021xRadiusServerEntry 4 }

	-- 1.3.6.1.4.1.6141.2.401.1.2.2.4.5
		 wwp8021xRadiusServerStatus OBJECT-TYPE
		      SYNTAX        RowStatus
		      MAX-ACCESS    read-create
		      STATUS        current
		      DESCRIPTION
		            "To create a row in this table, a manager must
		            set this object to either createAndGo(4).

		            A row in the WwpRadiusServerEntry can't be set to active until
		            wwpRadiusServerIpAddr has been set to valid value.

		            To disable a Radius server , the operator can set this object
		            to 'notInSerVice' state."
		      ::= { wwp8021xRadiusServerEntry 5 }


		-- 1.3.6.1.4.1.6141.2.401.1.3
		wwp8021xEvents OBJECT IDENTIFIER ::= { wwp8021xMIB 3 }


		-- 1.3.6.1.4.1.6141.2.401.1.3.0
		wwp8021xEventsV2 OBJECT IDENTIFIER ::= { wwp8021xEvents 0 }

		-- 1.3.6.1.4.1.6141.2.401.1.2.3
		wwp8021xSupplicantSecTable OBJECT-TYPE
			SYNTAX SEQUENCE OF Wwp8021xSupplicantSecEntry
			MAX-ACCESS not-accessible
			STATUS current
			DESCRIPTION
				"Table for Supplicant username and password. Has entry for every port on the switch"
			::= { wwp8021xObjs 3 }


		-- 1.3.6.1.4.1.6141.2.401.1.2.3.1
		wwp8021xSupplicantSecEntry OBJECT-TYPE
			SYNTAX Wwp8021xSupplicantSecEntry
			MAX-ACCESS not-accessible
			STATUS current
			DESCRIPTION
				"This contains the username and password entries for each port. Index is wwp8021xPort from Wwp8021xPortEntry"
			INDEX { wwp8021xPort }
			::= { wwp8021xSupplicantSecTable 1 }


		Wwp8021xSupplicantSecEntry ::=
			SEQUENCE {
				wwp8021xPort						INTEGER,
				wwp8021xSupplicantSecUserName	OCTET STRING,
				wwp8021xSupplicantSecPassword OCTET STRING
			 }


		-- 1.3.6.1.4.1.6141.2.401.1.2.3.1.1
		wwp8021xSupplicantSecUserName OBJECT-TYPE
			  SYNTAX       OCTET STRING(SIZE(0..63))
			  MAX-ACCESS   read-create
			  STATUS       current
			  DESCRIPTION
				  "User name associated with port. This is only applicable if port has role of Supplicant or Both"
			  ::= { wwp8021xSupplicantSecEntry 1 }

		-- 1.3.6.1.4.1.6141.2.401.1.2.3.1.2
		wwp8021xSupplicantSecPassword OBJECT-TYPE
			  SYNTAX       OCTET STRING(SIZE(0..63))
			  MAX-ACCESS   read-create
			  STATUS       current
			  DESCRIPTION
				  "Password associated with port. This is only applicable if port has role of Supplicant or Both"
			  ::= { wwp8021xSupplicantSecEntry 2 }

	END

--
-- WWP-8021X-MIB.my
--
