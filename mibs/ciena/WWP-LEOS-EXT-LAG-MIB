-- This file was included in WWP MIB release 04-10-01-0027
 --
 -- WWP-LEOS-EXT-LAG-MIB.my
 --
 --
 WWP-LEOS-EXT-LAG-MIB DEFINITIONS ::= BEGIN

 IMPORTS
    Integer32, Unsigned32, MODULE-IDENTITY, OBJECT-TYPE
        FROM SNMPv2-SMI
    DisplayString, RowStatus
        FROM SNMPv2-TC
    wwpModulesLeos
	FROM WWP-SMI;


 wwpLeosExtLagMIB MODULE-IDENTITY
	    LAST-UPDATED "200301151700Z"
	    ORGANIZATION "Ciena, Inc"
	    CONTACT-INFO
		    "   Mib Meister
		  			115 North Sullivan Road
					Spokane Valley, WA 99037
		        	USA
		        	Phone:  +1 509 242 9000
					Email:  support@ciena.com"
	    DESCRIPTION
		    "This MIB module is an extension to the IEEE8023-LAG-mib.
		    This MIB defines the managed objects for the creation and
		    deletion of Aggregators."
	    REVISION    "200301151700Z"
	    DESCRIPTION
		    "Initial creation."
	    ::= { wwpModulesLeos 14 }

 --
 -- Node definitions
 --

 wwpLeosExtLagMIBObjects OBJECT IDENTIFIER ::= { wwpLeosExtLagMIB 1 }

 wwpLeosExtLag  OBJECT IDENTIFIER ::= { wwpLeosExtLagMIBObjects 1 }

 -- Notifications

 wwpLeosExtLagMIBNotificationPrefix  OBJECT IDENTIFIER ::= { wwpLeosExtLagMIB 2 }
 wwpLeosExtLagMIBNotifications       OBJECT IDENTIFIER ::=
                       { wwpLeosExtLagMIBNotificationPrefix 0 }

 -- Conformance information

 wwpLeosExtLagMIBConformance OBJECT IDENTIFIER ::= { wwpLeosExtLagMIB 3 }
 wwpLeosExtLagMIBCompliances OBJECT IDENTIFIER ::= { wwpLeosExtLagMIBConformance 1 }
 wwpLeosExtLagMIBGroups      OBJECT IDENTIFIER ::= { wwpLeosExtLagMIBConformance 2 }

 wwpLeosMaxLags OBJECT-TYPE
    SYNTAX      Unsigned32
    MAX-ACCESS  read-only
    STATUS      current
    DESCRIPTION
        "The maximum number of aggregators that this device
        supports."
    ::= { wwpLeosExtLag 1 }

 wwpLeosNumLags OBJECT-TYPE
    SYNTAX      Unsigned32
    MAX-ACCESS  read-only
    STATUS      current
    DESCRIPTION
        "The current number of LAGs that are
        configured in this device."
    ::= { wwpLeosExtLag 2 }

 wwpLeosExtLagTable OBJECT-TYPE
     SYNTAX     SEQUENCE OF WwpLeosExtLagEntry
     MAX-ACCESS not-accessible
     STATUS     current
     DESCRIPTION
            "The (conceptual) table listing all the
	    aggregators."
     ::= { wwpLeosExtLag 3 }

 wwpLeosExtLagEntry OBJECT-TYPE
     SYNTAX      WwpLeosExtLagEntry
     MAX-ACCESS  not-accessible
     STATUS      current
     DESCRIPTION
           "An entry (conceptual row) in the wwpLeosExtLagTable."
     INDEX { wwpLeosExtAggId }
     ::= { wwpLeosExtLagTable 1 }

 WwpLeosExtLagEntry ::=  SEQUENCE {
     wwpLeosExtAggId                         Integer32,
     wwpLeosExtAggName                       DisplayString,
     wwpLeosExtAggIndex                      Integer32,
     wwpLeosExtAggStatus                     RowStatus,
     wwpLeosExtAggMode                       INTEGER,
     wwpLeosExtLagProtectionRevertState      INTEGER,
     wwpLeosExtLagProtectionRevertTimer      INTEGER,
     wwpLeosExtAggHashMode                   INTEGER,
     wwpLeosExtLagProtectionMode             INTEGER
 }

 wwpLeosExtAggId OBJECT-TYPE
     SYNTAX     Integer32 (1..2147483647)
     MAX-ACCESS read-only
     STATUS     current
     DESCRIPTION
           "Object which specifies a unique entry in the
           wwpLeosExtLagTable.  A management station wishing
           to create a LAG should use a pseudo-random value
	   for this object when creating an instance of a
           wwpLeosExtLagEntry."
     ::= { wwpLeosExtLagEntry 1 }

 wwpLeosExtAggName OBJECT-TYPE
     SYNTAX      DisplayString (SIZE(1..32))
     MAX-ACCESS  read-create
     STATUS      current
     DESCRIPTION
           "The name assigned to this Lag by the Management
	   station. This object can only be set while creating LAG.
	   It is not allowed to rename the LAG name once it is created."
     ::= { wwpLeosExtLagEntry 2 }

 wwpLeosExtAggIndex OBJECT-TYPE
    SYNTAX       Integer32 (1..2147483647)
    MAX-ACCESS   read-only
    STATUS       current
    DESCRIPTION
        "The unique identifier allocated to this Aggregator by
        the local System.  This attribute identifies an
        Aggregator instance among the subordinate managed
        objects of the containing object.
        This value is read-only. This object refer to the
	dot3adAggIndex in the IEEE-8023-LAG-MIB."
    REFERENCE
        "IEEE 802.3 Subclause 30.7.1.1.1"
    ::= { wwpLeosExtLagEntry 3 }

 wwpLeosExtAggStatus OBJECT-TYPE
     SYNTAX       RowStatus
     MAX-ACCESS   read-create
     STATUS       current
     DESCRIPTION
	     "Used to manage the creation and deletion of the
	     conceptual rows in this table.

             To create a row in this table, a manager must
             set this object to 'createAndGo'. To disable
	     the aggregator, a management should set this
	     object to 'notInService'."
     ::= { wwpLeosExtLagEntry 4 }

 wwpLeosExtAggMode OBJECT-TYPE
     SYNTAX      INTEGER {
			lacp(1),
			manual(2)
		 }
     MAX-ACCESS  read-write
     STATUS      current
     DESCRIPTION
           "This object specifies the mode in which given aggregation is operating."
     ::= { wwpLeosExtLagEntry 5 }

 wwpLeosExtLagProtectionRevertState OBJECT-TYPE
     SYNTAX      INTEGER {
     				on(1),
     				off(2)
     				}
     MAX-ACCESS  read-write
     STATUS      current
     DESCRIPTION
           "This object specifies that if the primary port goes from operationally disabled to operationally enabled it
            shall become active, and one of the secondary ports shall become backup if this MIB object is set to 'on' and the
            wwpLeosLagProtectionRevertTimer timer expires."
     ::= { wwpLeosExtLagEntry 6 }

 wwpLeosExtLagProtectionRevertTimer OBJECT-TYPE
     SYNTAX      INTEGER (0..60000)
     UNITS		 "msec"
     MAX-ACCESS  read-write
     STATUS      current
     DESCRIPTION
           "This object specifies the revert protection timer value."
     DEFVAL		{5000}
     ::= { wwpLeosExtLagEntry 7 }

 wwpLeosExtAggHashMode OBJECT-TYPE
     SYNTAX      INTEGER {
			mac-based(1),
			ip-based(2),
			enhanced(3)
		 }
     MAX-ACCESS  read-write
     STATUS      current
     DESCRIPTION
           "This object specifies the hash mode used by the aggregation for known unicast frames."
     ::= { wwpLeosExtLagEntry 8 }

 wwpLeosExtLagProtectionMode OBJECT-TYPE
     SYNTAX      INTEGER {
                        proprietary(1),
                        standard(2)
                 }
     MAX-ACCESS  read-write
     STATUS      current
     DESCRIPTION
           "This object specifies the LACP protection-mode in which given aggregation is operating."
     ::= { wwpLeosExtLagEntry 9 }

--
-- lag Mode Table
--
 wwpLeosLagModeTable OBJECT-TYPE
     SYNTAX     SEQUENCE OF WwpLeosLagModeEntry
     MAX-ACCESS not-accessible
     STATUS     current
     DESCRIPTION
            "The (conceptual) table listing the modes of aggregation on each port."
     ::= { wwpLeosExtLag 4 }

 wwpLeosLagModeEntry OBJECT-TYPE
     SYNTAX      WwpLeosLagModeEntry
     MAX-ACCESS  not-accessible
     STATUS      current
     DESCRIPTION
           "An entry (conceptual row) in the wwpLeosLagModeTable."
     INDEX { wwpLeosLagPhyPortId  }
     ::= { wwpLeosLagModeTable 1 }

 WwpLeosLagModeEntry ::=  SEQUENCE {
     wwpLeosLagPhyPortId	INTEGER,
     wwpLeosLagAdminMode	INTEGER,
     wwpLeosLagOperMode		INTEGER
 }

 wwpLeosLagPhyPortId OBJECT-TYPE
     SYNTAX      INTEGER (0..65535)
     MAX-ACCESS  read-only
     STATUS      current
     DESCRIPTION
           "This object specifies the physical port number.
	    It is also used as index in the table."
     ::= { wwpLeosLagModeEntry 1 }

 wwpLeosLagAdminMode OBJECT-TYPE
     SYNTAX      INTEGER {
			lacp(1),
			manual(2)
		 }
     MAX-ACCESS  read-write
     STATUS      current
     DESCRIPTION
           "This object specifies the administrative mode in which given port is operating."
     ::= { wwpLeosLagModeEntry 2 }

 wwpLeosLagOperMode OBJECT-TYPE
     SYNTAX      INTEGER {
			lacp(1),
			manual(2)
		 }
     MAX-ACCESS  read-only
     STATUS      current
     DESCRIPTION
           "This object specifies the operation mode in which given port is operating."
     ::= { wwpLeosLagModeEntry 3 }

--
-- lag Protection Table
--
 wwpLeosLagProtectionTable OBJECT-TYPE
     SYNTAX     SEQUENCE OF WwpLeosLagProtectionEntry
     MAX-ACCESS not-accessible
     STATUS     current
     DESCRIPTION
            "The (conceptual) table listing the protection ports for each aggregation."
     ::= { wwpLeosExtLag 5 }

 wwpLeosLagProtectionEntry OBJECT-TYPE
     SYNTAX      WwpLeosLagProtectionEntry
     MAX-ACCESS  not-accessible
     STATUS      current
     DESCRIPTION
           "An entry (conceptual row) in the wwpLeosLagProtectionTable."
     INDEX { wwpLeosExtAggId, wwpLeosLagProtectionPort  }
     ::= { wwpLeosLagProtectionTable 1 }

 WwpLeosLagProtectionEntry ::=  SEQUENCE {
     wwpLeosLagProtectionPort				INTEGER,
     wwpLeosLagProtectionRowStatus          RowStatus
 }

 wwpLeosLagProtectionPort OBJECT-TYPE
     SYNTAX      INTEGER (1..65535)
     MAX-ACCESS  read-only
     STATUS      current
     DESCRIPTION
           "This object specifies the protection port number. It is also used as index in the table."
     ::= { wwpLeosLagProtectionEntry 1 }

 wwpLeosLagProtectionRowStatus OBJECT-TYPE
     SYNTAX       RowStatus
     MAX-ACCESS   read-create
     STATUS       current
     DESCRIPTION
	     "Used to manage the creation and deletion of the
	     conceptual rows in this table.

             To create a row in this table, a manager must
             set this object to 'createAndGo'. To delete entry set this
	     	object to 'destroy'."
     ::= { wwpLeosLagProtectionEntry 2 }

--
-- lag system attributes
--
 wwpLeosExtAggFloodHashMode OBJECT-TYPE
     SYNTAX      INTEGER {
			simplified(1),
			enhanced(2)
		 }
     MAX-ACCESS  read-write
     STATUS      current
     DESCRIPTION
           "This object specifies the aggregation hash mode used by unknown
            unicast, multicast and broadcast frames for all aggregation ports
            in the system."
     ::= { wwpLeosExtLag 6 }

 END
