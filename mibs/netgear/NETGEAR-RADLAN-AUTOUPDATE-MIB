NETGEAR-RADLAN-AUTOUPDATE-MIB DEFINITIONS ::= BEGIN

IMPORTS
    rnd                             FROM NETGEAR-RADLAN-MIB
    MODULE-IDENTITY, OBJECT-TYPE    FROM SNMPv2-SMI
    DisplayString, TruthValue       FROM SNMPv2-TC
    ;


rlAutoUpdate MODULE-IDENTITY
    LAST-UPDATED "2007010600Z"
    ORGANIZATION "Radlan Computer Communications Ltd."
    CONTACT-INFO
        "radlan.com"
    DESCRIPTION
        "The Auto Update MIBs"
    ::={ rnd 123 }


rlAutoUpdateEnable OBJECT-TYPE
    SYNTAX  TruthValue
    MAX-ACCESS  read-write
    STATUS  current
    DESCRIPTION
        "Enable / Disable autoUpdateFeature"
    ::= { rlAutoUpdate 1 }

rlAutoUpdateFilesBoot OBJECT-TYPE
    SYNTAX TruthValue
    MAX-ACCESS  read-write
    STATUS  current
    DESCRIPTION
        "Defines whether a boot file should be auto updated"
    ::= { rlAutoUpdate 2 }

rlAutoUpdateFilesImage OBJECT-TYPE
    SYNTAX TruthValue
    MAX-ACCESS  read-write
    STATUS  current
    DESCRIPTION
        "Defines whether an image file should be auto updated"
    ::= { rlAutoUpdate 3 }

rlAutoUpdateFilesConf OBJECT-TYPE
    SYNTAX TruthValue
    MAX-ACCESS  read-write
    STATUS  current
    DESCRIPTION
        "Defines whether a configuration file should be auto updated"
    ::= { rlAutoUpdate 4 }

rlAutoUpdateCopyEnable OBJECT-TYPE
    SYNTAX  TruthValue
    MAX-ACCESS  read-write
    STATUS  current
    DESCRIPTION
        "Determines whether the running config will be saved in the startup config at the end of the process"
    ::= { rlAutoUpdate 5 }

rlAutoUpdatePreserveIP OBJECT-TYPE
    SYNTAX  TruthValue
    MAX-ACCESS  read-write
    STATUS  current
    DESCRIPTION
        "True means that the DHCP address will not be replaced by an address in the running config"
      ::= { rlAutoUpdate 6 }


END
