GSM7324-QOS-ACL-MIB DEFINITIONS ::= BEGIN

-- Copyright 2003 LVL7 Systems, Inc.  All rights reserved.

-- This SNMP Management Information Specification
-- embodies LVL7 System's confidential and proprietary
-- intellectual property.  LVL7 Systems retains all title
-- and ownership in the Specification including any revisions.

-- This Specification is supplied "AS IS", LVL7 Systems
-- makes no warranty, either expressed or implied,
-- as to the use, operation, condition, or performance of the
-- Specification.

    IMPORTS
      MODULE-IDENTITY, OBJECT-TYPE, IpAddress,
      Integer32, Unsigned32                             FROM SNMPv2-SMI
      RowStatus                                         FROM SNMPv2-TC
      gsm7324QOS                                        FROM GSM7324-QOS-MIB;

    gsm7324QOSACL MODULE-IDENTITY
    LAST-UPDATED "200305061200Z" -- 6 May 2003 12:00:00 GMT
    ORGANIZATION "Netgear"

    CONTACT-INFO
        ""
    DESCRIPTION
        ""
-- revision history
    REVISION
        "200305061200Z" -- 6 May 2003 12:00:00 GMT

    DESCRIPTION
        "Initial revision."
    ::= { gsm7324QOS 2 }


    --**************************************************************************************

    aclTable OBJECT-TYPE
         SYNTAX      SEQUENCE OF AclEntry
         MAX-ACCESS  not-accessible
         STATUS      current
         DESCRIPTION
                     "A table of ACL instances."
         ::= { gsm7324QOSACL 1 }

    aclEntry OBJECT-TYPE
         SYNTAX      AclEntry
         MAX-ACCESS  not-accessible
         STATUS      current
         DESCRIPTION
                     ""
         INDEX       { aclIndex }
         ::= { aclTable 1 }

    AclEntry ::= SEQUENCE {
           aclIndex
               Integer32,
           aclStatus
               RowStatus
           }

    aclStatus OBJECT-TYPE
         SYNTAX      RowStatus
         MAX-ACCESS  read-create
         STATUS      current
         DESCRIPTION
                     "Status of this instance.

                     active(1)      - this ACL instance is active
                     createAndGo(4) - set to this value to create an instance
                     destroy(6)     - set to this value to delete an instance"
         ::= { aclEntry 3 }


    aclIndex OBJECT-TYPE
         SYNTAX      Integer32
         MAX-ACCESS  not-accessible
         STATUS      current
         DESCRIPTION
                     "The ACL index this instance is associated with."
         ::= { aclEntry 1 }

    --**************************************************************************************

    aclIfTable OBJECT-TYPE
         SYNTAX      SEQUENCE OF AclIfEntry
         MAX-ACCESS  not-accessible
         STATUS      current
         DESCRIPTION
                     "A table of ACL interface instances."
         ::= { gsm7324QOSACL 2 }

    aclIfEntry OBJECT-TYPE
         SYNTAX      AclIfEntry
         MAX-ACCESS  not-accessible
         STATUS      current
         DESCRIPTION
                     ""
         INDEX       { aclIndex, aclIfIndex, aclIfDirection }
         ::= { aclIfTable 1 }

    AclIfEntry ::= SEQUENCE {
           aclIndex
               Integer32,
           aclIfIndex
               Integer32,
           aclIfDirection
               INTEGER,
           aclIfStatus
               RowStatus
           }

    aclIfIndex OBJECT-TYPE
         SYNTAX      Integer32
         MAX-ACCESS  not-accessible
         STATUS      current
         DESCRIPTION
                     "The interface this ACL instance is associated with."
         ::= { aclIfEntry 1 }

    aclIfDirection OBJECT-TYPE
         SYNTAX      INTEGER {
                      inbound(1),
                      outbound(2)
                     }
         MAX-ACCESS  not-accessible
         STATUS      current
         DESCRIPTION
                     "The direction this ACL instance applies."
         ::= { aclIfEntry 2 }

    aclIfStatus OBJECT-TYPE
         SYNTAX      RowStatus
         MAX-ACCESS  read-create
         STATUS      current
         DESCRIPTION
                     "Status of this instance.

                     active(1)      - this ACL index instance is active
                     createAndGo(4) - set to this value to assign an interface to an ACL
                     destroy(6)     - set to this value to remove an interface to an ACL"
         ::= { aclIfEntry 3 }


    --**************************************************************************************

    aclRuleTable OBJECT-TYPE
         SYNTAX      SEQUENCE OF AclRuleEntry
         MAX-ACCESS  not-accessible
         STATUS      current
         DESCRIPTION
                     "A table of ACL Rules instances."
         ::= { gsm7324QOSACL 3 }

    aclRuleEntry OBJECT-TYPE
         SYNTAX      AclRuleEntry
         MAX-ACCESS  not-accessible
         STATUS      current
         DESCRIPTION
                     "A table of ACL Classification Rules"
         INDEX       { aclIndex, aclRuleIndex }
         ::= { aclRuleTable 1 }

    AclRuleEntry ::= SEQUENCE {
           aclRuleIndex
               Integer32,
           aclRuleAction
               INTEGER,
           aclRuleProtocol
               Integer32,
           aclRuleSrcIpAddress
               IpAddress,
           aclRuleSrcIpMask
               IpAddress,
           aclRuleSrcL4Port
               Integer32,
           aclRuleSrcL4PortRangeStart
               Integer32,
           aclRuleSrcL4PortRangeEnd
               Integer32,
           aclRuleDestIpAddress
               IpAddress,
           aclRuleDestIpMask
               IpAddress,
           aclRuleDestL4Port
               Integer32,
           aclRuleDestL4PortRangeStart
               Integer32,
           aclRuleDestL4PortRangeEnd
               Integer32,
           aclRuleIPDSCP
               Integer32,
           aclRuleIpPrecedence
               Integer32,
           aclRuleIpTosBits
               Integer32,
           aclRuleIpTosMask
               Integer32,
           aclRuleStatus
               RowStatus
           }

    aclRuleIndex OBJECT-TYPE
         SYNTAX      Integer32
         MAX-ACCESS  not-accessible
         STATUS      current
         DESCRIPTION
                     "The index of this instance."
         ::= { aclRuleEntry 1 }

    aclRuleAction OBJECT-TYPE
         SYNTAX      INTEGER {
                      permit(1),
                      deny(2)
                      }
         MAX-ACCESS  read-create
         STATUS      current
         DESCRIPTION
                     "The type of action this rule should perform."
         DEFVAL { deny }
         ::= { aclRuleEntry 2 }

    aclRuleProtocol OBJECT-TYPE
         SYNTAX      Integer32 (1..255)
         MAX-ACCESS  read-create
         STATUS      current
         DESCRIPTION
                     "icmp - 1
                      igmp - 2
                      ip - 4
                      tcp - 6
                      udp - 17
                      All values from 1 to 255 are valid."
         ::= { aclRuleEntry 3 }

    aclRuleSrcIpAddress OBJECT-TYPE
         SYNTAX      IpAddress
         MAX-ACCESS  read-create
         STATUS      current
         DESCRIPTION
                     "The Source IP Address used in the ACL Classification."
         ::= { aclRuleEntry 4 }

    aclRuleSrcIpMask OBJECT-TYPE
         SYNTAX      IpAddress
         MAX-ACCESS  read-create
         STATUS      current
         DESCRIPTION
                     "The Source IP Mask used in the ACL Classification."
         ::= { aclRuleEntry 5 }

    aclRuleSrcL4Port OBJECT-TYPE
         SYNTAX      Integer32
         MAX-ACCESS  read-create
         STATUS      current
         DESCRIPTION
                     "The Source Port Number (Layer 4) used in the ACL Classification."
         ::= { aclRuleEntry 6 }

    aclRuleSrcL4PortRangeStart OBJECT-TYPE
         SYNTAX      Integer32
         MAX-ACCESS  read-create
         STATUS      current
         DESCRIPTION
                     "The Source Port Number(Layer 4) range start."
         ::= { aclRuleEntry 7 }

    aclRuleSrcL4PortRangeEnd OBJECT-TYPE
         SYNTAX      Integer32
         MAX-ACCESS  read-create
         STATUS      current
         DESCRIPTION
                     "The Source Port Number(Layer 4) range end."
         ::= { aclRuleEntry 8 }

    aclRuleDestIpAddress OBJECT-TYPE
         SYNTAX      IpAddress
         MAX-ACCESS  read-create
         STATUS      current
         DESCRIPTION
                     "The Destination IP Address used in the ACL Classification."
         ::= { aclRuleEntry 9 }

    aclRuleDestIpMask OBJECT-TYPE
         SYNTAX      IpAddress
         MAX-ACCESS  read-create
         STATUS      current
         DESCRIPTION
                     "The Destination IP Mask used in the ACL Classification."
         ::= { aclRuleEntry 10 }

    aclRuleDestL4Port OBJECT-TYPE
         SYNTAX      Integer32
         MAX-ACCESS  read-create
         STATUS      current
         DESCRIPTION
                     "The Destination Port (Layer 4) used in ACl classification."
         ::= { aclRuleEntry 11 }

    aclRuleDestL4PortRangeStart OBJECT-TYPE
         SYNTAX      Integer32
         MAX-ACCESS  read-create
         STATUS      current
         DESCRIPTION
                     "The Destination Port (Layer 4) starting range used in ACL classification."
         ::= { aclRuleEntry 12 }

    aclRuleDestL4PortRangeEnd OBJECT-TYPE
         SYNTAX      Integer32
         MAX-ACCESS  read-create
         STATUS      current
         DESCRIPTION
                     "The Destination Port (Layer 4) ending range used in ACL classification."
         ::= { aclRuleEntry 13 }

    aclRuleIPDSCP OBJECT-TYPE
         SYNTAX      Integer32
         MAX-ACCESS  read-create
         STATUS      current
         DESCRIPTION
                     "The Differentiated Services Code Point value."
         ::= { aclRuleEntry 14 }

    aclRuleIpPrecedence OBJECT-TYPE
         SYNTAX      Integer32
         MAX-ACCESS  read-create
         STATUS      current
         DESCRIPTION
                     "The Type of Service (TOS) IP Precedence value."
         ::= { aclRuleEntry 15 }

    aclRuleIpTosBits OBJECT-TYPE
         SYNTAX      Integer32
         MAX-ACCESS  read-create
         STATUS      current
         DESCRIPTION
                     "The Type of Service (TOS) Bits value."
         ::= { aclRuleEntry 16 }

    aclRuleIpTosMask OBJECT-TYPE
         SYNTAX      Integer32
         MAX-ACCESS  read-create
         STATUS      current
         DESCRIPTION
                     "The Type of Service (TOS) Mask value."
         ::= { aclRuleEntry 17 }

    aclRuleStatus OBJECT-TYPE
         SYNTAX      RowStatus
         MAX-ACCESS  read-create
         STATUS      current
         DESCRIPTION
                     "Status of this instance.

                     active(1)      - this ACL Rule is active
                     createAndGo(4) - set to this value to create an instance
                     destroy(6)     - set to this value to delete an instance"
         ::= { aclRuleEntry 18 }
END
