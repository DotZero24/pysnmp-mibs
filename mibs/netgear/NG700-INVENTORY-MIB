NG700-INVENTORY-MIB DEFINITIONS ::= BEGIN

-- Copyright Netgear Inc (2003-2007) All rights reserved.

-- This SNMP Management Information Specification
-- embodies Netgear Inc's confidential and proprietary
-- intellectual property.  Netgear Inc retains all title
-- and ownership in the Specification including any revisions.

-- This Specification is supplied "AS IS", Netgear Inc
-- makes no warranty, either expressed or implied,
-- as to the use, operation, condition, or performance of the
-- Specification.

    IMPORTS
        MODULE-IDENTITY, OBJECT-TYPE, Integer32, Gauge32, Counter32,
        Unsigned32, TimeTicks, NOTIFICATION-TYPE  FROM SNMPv2-SMI
        TEXTUAL-CONVENTION, DisplayString,
        RowStatus                                 FROM SNMPv2-TC
        MODULE-COMPLIANCE, OBJECT-GROUP, NOTIFICATION-GROUP
                                                  FROM SNMPv2-CONF
        ng700smartswitch                                  FROM NG700-REF-MIB;

    fastPathInventory MODULE-IDENTITY
        LAST-UPDATED "201101260000Z" -- 26 Jan 2011 12:00:00 GMT
        ORGANIZATION "Netgear Inc"
        CONTACT-INFO ""
        DESCRIPTION
            "This MIB defines the objects used for FastPath to
            configure and report information and status of units,
            slots and supported cards."

        -- Revision history.
        REVISION
            "201101260000Z" -- 26 Jan 2011 12:00:00 GMT
        DESCRIPTION
            "Postal address updated."
        REVISION
            "200705230000Z" -- 23 May 2007 12:00:00 GMT
        DESCRIPTION
            "Netgear branding related changes."
        REVISION
            "200410282037Z" -- Thu Jun 26 20:37:34 2003 GMT
        DESCRIPTION
            "Version 2 - Add support for Front Panel Stacking configuration."
        REVISION
            "200305261930Z" -- Thu Jun 26 19:30:54 2003 GMT
        DESCRIPTION
            "Initial version."

        ::= { ng700smartswitch 13 }

    AgentInventoryUnitPreference ::= TEXTUAL-CONVENTION
        STATUS      current
        DESCRIPTION
            "Indicates the preference the unit has for being the
            management unit in the stack.  If the value is 0, it
            indicates the unit is disabled for management."
        SYNTAX  INTEGER {
                 disabled(0),
                 unsassigned(1),
                 assigned(2)
                 }

    AgentInventoryUnitType ::= TEXTUAL-CONVENTION
        DISPLAY-HINT "x"
        STATUS      current
        DESCRIPTION
            "The Unit Type value for a given unit, displayed in hexadecimal."
        SYNTAX  Unsigned32

    AgentInventoryCardType ::= TEXTUAL-CONVENTION
        DISPLAY-HINT "x"
        STATUS      current
        DESCRIPTION
            "The Card Type value for a given card, displayed in hexadecimal."
        SYNTAX  Unsigned32

    --**************************************************************************************
    -- agentInventoryStackGroup
    --
    --**************************************************************************************
    agentInventoryStackGroup                      OBJECT IDENTIFIER ::= { fastPathInventory 1 }

    agentInventoryStackSTKname OBJECT-TYPE
        SYNTAX      INTEGER {
                    unconfigured(1),
                    image1(2),
                    image2(3)
                    }
        MAX-ACCESS  read-write
        STATUS      current
        DESCRIPTION
            "STK file on management unit for copy/activate/delete operations to all units in the stack
             unconfigured(1) - indicates a default state and can not be set."
        ::= { agentInventoryStackGroup 5 }

    agentInventoryStackActivateSTK OBJECT-TYPE
        SYNTAX      INTEGER {
                    enable(1),
                    disable(2)
                    }
        MAX-ACCESS  read-write
        STATUS      current
        DESCRIPTION
            "Activates the specified STK file on all units on the stack."
        ::= { agentInventoryStackGroup 6 }

    agentInventoryStackDeleteSTK OBJECT-TYPE
        SYNTAX      INTEGER {
                    enable(1),
                    disable(2)
                    }
        MAX-ACCESS  read-write
        STATUS      current
        DESCRIPTION
            "Deletes the specified STK file from all units on the stack."
        ::= { agentInventoryStackGroup 7 }

    --**************************************************************************************
    -- agentInventoryCardGroup
    --
    --**************************************************************************************

    agentInventoryCardGroup                       OBJECT IDENTIFIER ::= { fastPathInventory 4 }

    --**************************************************************************************
    -- agentInventoryCardTypeTable
    --
    --**************************************************************************************

    agentInventoryCardTypeTable OBJECT-TYPE
        SYNTAX         SEQUENCE OF AgentInventoryCardTypeEntry
        MAX-ACCESS     not-accessible
        STATUS         current
        DESCRIPTION
            "Contains information for all supported Card Types in the system."
        ::= { agentInventoryCardGroup 1 }

    agentInventoryCardTypeEntry OBJECT-TYPE
        SYNTAX         AgentInventoryCardTypeEntry
        MAX-ACCESS     not-accessible
        STATUS         current
        DESCRIPTION
            "Contains information related to a specific Card Type."
        INDEX          { agentInventoryCardIndex }
        ::= { agentInventoryCardTypeTable 1 }

    AgentInventoryCardTypeEntry ::=
        SEQUENCE {
         agentInventoryCardIndex
                 Unsigned32,
         agentInventoryCardType
                 AgentInventoryCardType,
         agentInventoryCardModelIdentifier
                 DisplayString,
         agentInventoryCardDescription
                 DisplayString
         }

    agentInventoryCardIndex OBJECT-TYPE
        SYNTAX      Unsigned32
        MAX-ACCESS  not-accessible
        STATUS      current
        DESCRIPTION
            "An arbitrary index used to identify cards in the table."
        ::= { agentInventoryCardTypeEntry 1 }

    agentInventoryCardType OBJECT-TYPE
        SYNTAX      AgentInventoryCardType
        MAX-ACCESS  read-only
        STATUS      current
        DESCRIPTION
            "The Card Type associated with this instance."
        ::= { agentInventoryCardTypeEntry 2 }

    agentInventoryCardModelIdentifier OBJECT-TYPE
        SYNTAX      DisplayString
        MAX-ACCESS  read-only
        STATUS      current
        DESCRIPTION
            "The model identifier for the supported Card Type."
        ::= { agentInventoryCardTypeEntry 3 }

    agentInventoryCardDescription OBJECT-TYPE
        SYNTAX      DisplayString
        MAX-ACCESS  read-only
        STATUS      current
        DESCRIPTION
            "The card description for the supported Card Type."
        ::= { agentInventoryCardTypeEntry 4 }

    --**************************************************************************************
    -- agentInventoryComponentGroup
    --
    --**************************************************************************************

    agentInventoryComponentGroup                  OBJECT IDENTIFIER ::= { fastPathInventory 5 }


    --**************************************************************************************
    -- agentInventoryComponentTable
    --
    --**************************************************************************************

    agentInventoryComponentTable OBJECT-TYPE
        SYNTAX         SEQUENCE OF AgentInventoryComponentEntry
        MAX-ACCESS     not-accessible
        STATUS         current
        DESCRIPTION
            "Contains information for all supported Components in the system."
        ::= { agentInventoryComponentGroup 1 }

    agentInventoryComponentEntry OBJECT-TYPE
        SYNTAX         AgentInventoryComponentEntry
        MAX-ACCESS     not-accessible
        STATUS         current
        DESCRIPTION
            "Contains information related to a specific Components."
        INDEX          { agentInventoryComponentIndex }
        ::= { agentInventoryComponentTable 1 }

    AgentInventoryComponentEntry ::=
        SEQUENCE {
         agentInventoryComponentIndex
                 Unsigned32,
         agentInventoryComponentMnemonic
                 DisplayString,
         agentInventoryComponentName
                 DisplayString
         }

    agentInventoryComponentIndex OBJECT-TYPE
        SYNTAX      Unsigned32
        MAX-ACCESS  not-accessible
        STATUS      current
        DESCRIPTION
            "An arbitrary index used to reference components in the table."
        ::= { agentInventoryComponentEntry 1 }

    agentInventoryComponentMnemonic OBJECT-TYPE
        SYNTAX      DisplayString
        MAX-ACCESS  read-only
        STATUS      current
        DESCRIPTION
            "The abreviated name of this component."
        ::= { agentInventoryComponentEntry 2 }

    agentInventoryComponentName OBJECT-TYPE
        SYNTAX      DisplayString
        MAX-ACCESS  read-only
        STATUS      current
        DESCRIPTION
            "The name of the component for this instance."
        ::= { agentInventoryComponentEntry 3 }

END
