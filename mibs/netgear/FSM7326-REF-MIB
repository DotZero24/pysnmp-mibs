FSM7326-REF-MIB DEFINITIONS ::= BEGIN

-- Copyright 2003 LVL7 Systems, Inc.  All rights reserved.

-- This SNMP Management Information Specification
-- embodies LVL7 System's confidential and proprietary
-- intellectual property.  LVL7 Systems retains all title
-- and ownership in the Specification including any revisions.

-- This Specification is supplied "AS IS", LVL7 Systems
-- makes no warranty, either expressed or implied,
-- as to the use, operation, condition, or performance of the
-- Specification.

    IMPORTS
      enterprises                                       FROM RFC1155-SMI;


netgear            OBJECT IDENTIFIER ::= { enterprises 4526 }
snmpManagedSwitch  OBJECT IDENTIFIER ::= { netgear 1 }

    fsm7326 MODULE-IDENTITY
    LAST-UPDATED "200311101200Z" -- 10 Nov 2003 12:00:00 GMT
    ORGANIZATION "Netgear"

    CONTACT-INFO
        ""
    DESCRIPTION
        ""
-- revision history
    REVISION
	    "200305061200Z" -- 22 Aug 2003 12:00:00 GMT

	DESCRIPTION
	    "Initial revision."
    ::= {  snmpManagedSwitch 9 }


-- New Textual Conventions
AgentPortMask ::= TEXTUAL-CONVENTION
   STATUS  current
   DESCRIPTION
       "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'

        When setting this value, the system will ignore
        configuration for ports not between the first and last
        valid ports.  Configuration of any port numbers between
        this range that are not valid ports return a failure
        message, but will still apply configuration for valid
        ports."
   SYNTAX  OCTET STRING


END
