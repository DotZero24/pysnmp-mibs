NETGEAR-ME-MIB DEFINITIONS ::= BEGIN



IMPORTS
        enterprises
       , IpAddress
                        FROM RFC1155-SMI
        DisplayString
       , PhysAddress
                        FROM RFC1213-MIB
        OBJECT-TYPE                         FROM RFC-1212
        TRAP-TYPE                           FROM RFC-1215;




netgear			OBJECT IDENTIFIER ::= { enterprises 4526 }
wirelessProducts		OBJECT IDENTIFIER ::= { netgear 4 }


wirelessAccessPointDev OBJECT IDENTIFIER
        ::= { wirelessProducts 1 }



wirelessAPSystemGroup	OBJECT IDENTIFIER ::= { wirelessAccessPointDev 1 }
wirelessAPConnectedStationGroup	OBJECT IDENTIFIER ::= { wirelessAccessPointDev 2 }
wirelessAPIfTrafficGroup	OBJECT IDENTIFIER ::= { wirelessAccessPointDev 3 }
wirelessAPIfSettingsGroup	OBJECT IDENTIFIER ::= { wirelessAccessPointDev 4 }
wirelessAPWirelessSettingsGroup	OBJECT IDENTIFIER ::= { wirelessAccessPointDev 5 }
wirelessAPSecuritySettingsGroup	OBJECT IDENTIFIER ::= { wirelessAccessPointDev 6 }




wirelessAPMacAddr OBJECT-TYPE
	SYNTAX		PhysAddress
	ACCESS		read-only
	STATUS		mandatory
	DESCRIPTION
		"Access Point MAC address, It will be like '00c002003009'"
	::= { wirelessAPSystemGroup 1 }

wirelessAPFWVer OBJECT-TYPE
	SYNTAX		DisplayString
	ACCESS		read-only
	STATUS		mandatory
	DESCRIPTION
		"Access Point firmware version, It will be like 'Version 2.0 Release 08'"
	::= { wirelessAPSystemGroup 2 }

wirelessAPDateTime OBJECT-TYPE
        SYNTAX      DisplayString
        ACCESS  read-only
        STATUS      mandatory
        DESCRIPTION
            "The date and time, with optional timezone
             information. It will be like '2003-04-03 02:50:54 GMT'"
        ::= { wirelessAPSystemGroup 3 }

wirelessAPUpTime OBJECT-TYPE
	SYNTAX  	TimeTicks
      ACCESS  read-only
      STATUS  	mandatory
      DESCRIPTION
           "The time (in hundredths of a second) since the
            network management portion of the system was last
            re-initialized.
            It will like '11223533' in the unit of 1/100second.
		This object value is the same as MIB-II sysUpTime object"
	::= { wirelessAPSystemGroup 4 }

wirelessAPResetNow OBJECT-TYPE
        SYNTAX      INTEGER  {
                    not-reset(0),
                    reset(1)
                        }

        ACCESS  read-write
        STATUS      mandatory
        DESCRIPTION
            "Setting this object to true(1) causes the device to reset.
             Reading this object always returns false(2)."
        ::= { wirelessAPSystemGroup 5 }

wirelessAPResetToFactoryDefault OBJECT-TYPE
        SYNTAX      INTEGER{
                     not-erase(0),
                     erase(1)
                    }
        ACCESS  read-write
        STATUS      mandatory
        DESCRIPTION
            "Setting this object to true(1) causes the device to reset 		to factory default value. Reading this object always 			returns false(2)."
        ::= { wirelessAPSystemGroup 6 }

wirelessAPPassword OBJECT-TYPE
	SYNTAX	DisplayString (SIZE(4..20))
	ACCESS	read-write
	STATUS		mandatory
	DESCRIPTION
		"Get/Set the password"
	::= { wirelessAPSystemGroup 7 }


wirelessAPClearLog OBJECT-TYPE
	SYNTAX	INTEGER {
             not-clear(0),
             clear(1)
                }
	ACCESS	read-write
	STATUS		mandatory
	DESCRIPTION
		"Setting this value clear(1) causes the AP to clear the log data,
         Reading this walue always return not-clear(0)."
	::= { wirelessAPSystemGroup 8 }

wirelessAPSaveConfiguration OBJECT-TYPE
	SYNTAX	INTEGER {
             not-save(0),
             save(1)
                }
	ACCESS	read-write
	STATUS		mandatory
	DESCRIPTION
		"Setting this value save(1) causes the settings changed by SNMP to be stored forever but in memory,
         Reading this walue always return save(0)."
	::= { wirelessAPSystemGroup 9 }

snmpTrapVersion OBJECT-TYPE
	SYNTAX	INTEGER {
             V1(0),
             V2c(1)
                }
	ACCESS	read-write
	STATUS		mandatory
	DESCRIPTION
		" "
	::= { wirelessAPSystemGroup 10 }

snmpTrapRcvIpType OBJECT-TYPE
	SYNTAX	INTEGER {
             Uni-cast(0),
             Broadcast(1)
                }
	ACCESS	read-write
	STATUS		mandatory
	DESCRIPTION
		" "
	::= { wirelessAPSystemGroup 11 }

snmpAPTrapRcvIpAddress OBJECT-TYPE
        SYNTAX  IpAddress
        ACCESS read-write
        STATUS mandatory
        DESCRIPTION
            " "
        ::= {wirelessAPSystemGroup 12 }

snmpAPSNMPEnable OBJECT-TYPE
        	SYNTAX	INTEGER {
             Disable(0),
             Enable(1)
                }
        ACCESS read-write
        STATUS mandatory
        DESCRIPTION
            " "
        ::= {wirelessAPSystemGroup 13 }

snmpAPCommunity OBJECT-TYPE
        SYNTAX DisplayString (SIZE(0..7))
        ACCESS read-write
        STATUS mandatory
        DESCRIPTION
            " "
        ::= {wirelessAPSystemGroup 14 }

snmpAPAccessRight OBJECT-TYPE
        SYNTAX	INTEGER {
             Read-Only(0),
             Read-and-Write(1)
                }
        ACCESS read-write
        STATUS mandatory
        DESCRIPTION
            " "
        ::= {wirelessAPSystemGroup 15 }

snmpAPManagersType OBJECT-TYPE
        SYNTAX	INTEGER {
             A-Specific-Station(0),
             Any-Station(1)
                }
        ACCESS read-write
        STATUS mandatory
        DESCRIPTION
            " "
        ::= {wirelessAPSystemGroup 16 }

snmpAPSpecificStationIp OBJECT-TYPE
        SYNTAX  IpAddress
        ACCESS read-write
        STATUS mandatory
        DESCRIPTION
            " "
        ::= {wirelessAPSystemGroup 17 }

snmpAPTrapEnable OBJECT-TYPE
        SYNTAX	INTEGER {
             Disable(0),
             Enable(1)
                }
        ACCESS read-write
        STATUS mandatory
        DESCRIPTION
            " "
        ::= {wirelessAPSystemGroup 18 }


wirelessAPConnectedStationTableRefresh OBJECT-TYPE
	SYNTAX	INTEGER	{
			not-refresh(0)
			refresh(1)
		}
    ACCESS  read-write
    STATUS      mandatory
    DESCRIPTION
	"Setting this value to refresh(1), the wireless AP will start the conntected Station Table refresh progress.
	Reading this vlaue always return not-refresh(1)"
	DEFVAL { 2 }
    ::= { wirelessAPConnectedStationGroup 1 }

wirelessAPConnectedStation OBJECT IDENTIFIER ::= { wirelessAPConnectedStationGroup 2 }

wirelessAPConnectedStationTable	OBJECT-TYPE
	SYNTAX		SEQUENCE OF WirelessAPConnectedStationEntry
	ACCESS	not-accessible
	STATUS		mandatory
	DESCRIPTION
		"Wireless AP Connected Station Table Object"
	::= { wirelessAPConnectedStation 1 }

wirelessAPConnectedStationEntry	OBJECT-TYPE
	SYNTAX		WirelessAPConnectedStationEntry
	ACCESS	not-accessible
	STATUS		mandatory
	DESCRIPTION
		"An entry containing information for Wireless AP Connected Station Table"
	INDEX	{ wirelessAPConnectedStationMacAddr }
	::= { wirelessAPConnectedStationTable 1 }

WirelessAPConnectedStationEntry ::=
	SEQUENCE {
		wirelessAPConnectedStationMacAddr		PhysAddress,
		wirelessAPConnectedStationStatus		INTEGER,

	}


wirelessAPConnectedStationMacAddr		OBJECT-TYPE
	SYNTAX		PhysAddress
	ACCESS	read-only
	STATUS		mandatory
	DESCRIPTION
		"Wireless Connected Station Mac Address"
	::= { wirelessAPConnectedStationEntry 2 }

wirelessAPConnectedStationStatus		OBJECT-TYPE
	SYNTAX		INTEGER {
					associated(0),
					athenticating(1),
					authenticated(2),
					not-associated(3)
				}
	ACCESS	read-only
	STATUS		mandatory
	DESCRIPTION
		"Wireless Connected Station Status"
	::= { wirelessAPConnectedStationEntry 3 }




wirelessAPControl	OBJECT-TYPE
	SYNTAX	INTEGER {
			off(0),
			on(1)
			}
	ACCESS	read-write
	STATUS	mandatory
	DESCRIPTION
		"Wireless Access Point Control"
	DEFVAL { 0}
 	::= { wirelessAPConnectedStationGroup 3 }

wirelessAPControlList OBJECT IDENTIFIER ::= { wirelessAPConnectedStationGroup 4 }

wirelessAPControlListTable OBJECT-TYPE
	SYNTAX		SEQUENCE OF WirelessAPControlListEntry
	ACCESS	not-accessible
	STATUS		mandatory
	DESCRIPTION
		"Wireless Access Point Control List Table Object"
	::= { wirelessAPControlList 1 }

wirelessAPControlListEntry OBJECT-TYPE
	SYNTAX		WirelessAPControlListEntry
	ACCESS	not-accessible
	STATUS		mandatory
	DESCRIPTION
		"An entry containing information for Wireless Access Point Control List Table Object"
	INDEX { wirelessAPControlListMacAddr }
	::= { wirelessAPControlListTable 1 }

WirelessAPControlListEntry ::= SEQUENCE {
	wirelessAPControlListMacAddr		PhysAddress

	}


wirelessAPControlListMacAddr OBJECT-TYPE
		SYNTAX		PhysAddress
		ACCESS	read-write
		STATUS		mandatory
		DESCRIPTION
			"Wireless Access Point Control List Mac Address"
		::= { wirelessAPControlListEntry 2 }




wirelessAPCtlOperate OBJECT IDENTIFIER ::= {wirelessAPConnectedStationGroup 5}
wirelessAPAddCtlMacAddr OBJECT-TYPE
        SYNTAX  PhysAddress
        ACCESS read-write
        STATUS mandatory
        DESCRIPTION
            "The added entry's Physical Address,
             Reading this object always return '000000000000'"
        ::= {wirelessAPCtlOperate 1}

wirelessAPDelCtlMacAddr OBJECT-TYPE
        SYNTAX  PhysAddress
        ACCESS read-write
        STATUS mandatory
        DESCRIPTION
            "The deleted entry's Physical Address,
             Reading this object always return '000000000000'"
        ::= {wirelessAPCtlOperate 2}



wirelessAPIfWiredTrafficGroup OBJECT IDENTIFIER
	::= { wirelessAPIfTrafficGroup 1 }

wirelessAPIfWlanTrafficGroup OBJECT IDENTIFIER
	::= { wirelessAPIfTrafficGroup 2 }


wirelessAPIfWiredTotalOctetsIn OBJECT-TYPE
	SYNTAX	Counter32
	ACCESS	read-only
	STATUS	mandatory
	DESCRIPTION
		"Traffic received by the wireless AP via Ethernet in octets"
	::= { wirelessAPIfWiredTrafficGroup 1 }

wirelessAPIfWiredTotalOctetsOut OBJECT-TYPE
	SYNTAX	Counter32
	ACCESS	read-only
	STATUS	mandatory
	DESCRIPTION
		"Traffic transmitted by the wireless AP via Ethernet in octets"
	::= { wirelessAPIfWiredTrafficGroup 2 }

wirelessAPIfWiredPacketsIn OBJECT-TYPE
	SYNTAX	Counter32
	ACCESS	read-only
	STATUS	mandatory
	DESCRIPTION
		"Traffic received by the wireless AP via Ethernet in packets"
	::= { wirelessAPIfWiredTrafficGroup 3 }

wirelessAPIfWiredPacketsOut OBJECT-TYPE
	SYNTAX	Counter32
	ACCESS	read-only
	STATUS	mandatory
	DESCRIPTION
		"Traffic transmitted by the wireless AP via Ethernet in packets."
	::= { wirelessAPIfWiredTrafficGroup 4 }

wirelessAPIfWiredThroughputIn	OBJECT-TYPE
	SYNTAX	Counter32
	ACCESS	read-only
	STATUS	mandatory
	DESCRIPTION
		"Throughput-in at Ethernet  by the wireless AP in the unit of B/s"
	::= { wirelessAPIfWiredTrafficGroup 5 }

wirelessAPIfWiredThroughputOut OBJECT-TYPE
	SYNTAX	Counter32
	ACCESS	read-only
	STATUS	mandatory
	DESCRIPTION
		"Throughput-out at Ethernet by the wireless AP in the unit of B/s"
	::= { wirelessAPIfWiredTrafficGroup 6 }

wirelessAPIfWiredErrorsIn	OBJECT-TYPE
	SYNTAX	Counter32
	ACCESS	read-only
	STATUS	mandatory
	DESCRIPTION
		"CRC errors in in-traffic occurs at Ethernet by the wireless AP"
	::= { wirelessAPIfWiredTrafficGroup 7 }

wirelessAPIfWiredErrorsOut OBJECT-TYPE
	SYNTAX	Counter32
	ACCESS	read-only
	STATUS	mandatory
	DESCRIPTION
		"CRC errors in out-traffic occurs at Ethernet by the wireless AP"
	::= { wirelessAPIfWiredTrafficGroup 8 }

wirelessAPIfWiredTrafficResetCounter OBJECT-TYPE
	SYNTAX	INTEGER {
				false(0),
				true(1)
			}
	ACCESS	read-write
	STATUS	mandatory
	DESCRIPTION
		"Reset the Etherenet interface both Octets In and Out counters"
	::= { wirelessAPIfWiredTrafficGroup 9 }

wirelessAPIfWLANTotalOctetsIn OBJECT-TYPE
	SYNTAX	Counter32
	ACCESS	read-only
	STATUS	mandatory
	DESCRIPTION
		"Traffic received via WLAN by the wireless AP in octets"
	::= { wirelessAPIfWlanTrafficGroup 1 }

wirelessAPIfWLANTotalOctetsOut OBJECT-TYPE
	SYNTAX	Counter32
	ACCESS	read-only
	STATUS	mandatory
	DESCRIPTION
		"Traffic transmitted via WLAN by the wireless AP in octets"
	::= { wirelessAPIfWlanTrafficGroup 2 }

wirelessAPIfWLANUnicastPacketsIn OBJECT-TYPE
	SYNTAX	Counter32
	ACCESS	read-only
	STATUS	mandatory
	DESCRIPTION
		"Unicast traffic received via WLAN by the wireless AP in packets"
	::= { wirelessAPIfWlanTrafficGroup 3 }

wirelessAPIfWLANUnicastPacketsOut OBJECT-TYPE
	SYNTAX	Counter32
	ACCESS	read-only
	STATUS	mandatory
	DESCRIPTION
		"Unicast traffic transmitted via WLAN by the wireless AP in packets"
	::= { wirelessAPIfWlanTrafficGroup 4 }

wirelessAPIfWLANBroadcastPacketsIn	OBJECT-TYPE
	SYNTAX	Counter32
	ACCESS	read-only
	STATUS	mandatory
	DESCRIPTION
		"Broadcast traffic received via WLAN by the wireless AP in packets"
	::= { wirelessAPIfWlanTrafficGroup 5 }

wirelessAPIfWLANBroadcastPacketsOut OBJECT-TYPE
	SYNTAX	Counter32
	ACCESS	read-only
	STATUS	mandatory
	DESCRIPTION
		"Broadcast traffic transmitted via WLAN by the wireless AP in packets"
	::= { wirelessAPIfWlanTrafficGroup 6 }

wirelessAPIfWLANMulticastPacketsIn	OBJECT-TYPE
	SYNTAX	Counter32
	ACCESS	read-only
	STATUS	mandatory
	DESCRIPTION
		"Multicast traffic received via WLAN by the wireless AP in packets"
	::= { wirelessAPIfWlanTrafficGroup 7 }

wirelessAPIfWLANMulticastPacketsOut OBJECT-TYPE
	SYNTAX	Counter32
	ACCESS	read-only
	STATUS	mandatory
	DESCRIPTION
		"Multicast traffic transmitted via WLAN by the wireless AP in packets"
	::= { wirelessAPIfWlanTrafficGroup 8 }


wirelessAPIfWLANThroughputIn OBJECT-TYPE
	SYNTAX	Counter32
	ACCESS	read-only
	STATUS	mandatory
	DESCRIPTION
		"Throughtput-in at WLAN transmitted by the wireless AP in the unit of B/s"
	::= { wirelessAPIfWlanTrafficGroup 9 }

wirelessAPIfWLANThroughputOut OBJECT-TYPE
	SYNTAX	Counter32
	ACCESS	read-only
	STATUS	mandatory
	DESCRIPTION
		"Throughtput-out at WLAN transmitted by the wireless AP in the unit of B/s"
	::= { wirelessAPIfWlanTrafficGroup 10 }

wirelessAPIfWLANPacketsIn OBJECT-TYPE
	SYNTAX	Counter32
	ACCESS	read-only
	STATUS	mandatory
	DESCRIPTION
		"Total in-packets at WLAN received by the wireless AP in packets"
	::= { wirelessAPIfWlanTrafficGroup 11 }

wirelessAPIfWLANPacketsOut OBJECT-TYPE
	SYNTAX	Counter32
	ACCESS	read-only
	STATUS	mandatory
	DESCRIPTION
		"Total out-packets at WLAN transmitted by the wireless AP in packets"
	::= { wirelessAPIfWlanTrafficGroup 12 }

wirelessAPIfWLANTrafficResetCounter OBJECT-TYPE
	SYNTAX	INTEGER {
				false(0),
				true(1)
			}
	ACCESS	read-write
	STATUS	mandatory
	DESCRIPTION
		"Reset the WLAN interface 's counters, they will start from 0 again."
	::= { wirelessAPIfWlanTrafficGroup 13 }






wirelessAPDHCPClientObtainIPchoice OBJECT-TYPE
	SYNTAX	INTEGER {
				static(0),
				automatic(1)
			}
	ACCESS	read-write
	STATUS		mandatory
	DESCRIPTION
		"Wireless Access Point DHCP Client Obtain an IP address choice
		static(0) means use static IP addess;
		automatic(1) means obtain an IP address automatically from
		DHCP server"
	DEFVAL { 0 }
	::= { wirelessAPIfSettingsGroup 1 }

wirelessAPDHCPClientIPaddr OBJECT-TYPE
	SYNTAX	IpAddress
	ACCESS	read-only
	STATUS		mandatory
	DESCRIPTION
		"Wireless Access Point DHCP Client IP address
		If wirelessAPDHCPClientObtainIPchoice is set to static(0),
		then it should be the same as
		wirelessAPDHCPClientStaticIPaddr."
	::= { wirelessAPIfSettingsGroup 2 }

wirelessAPDHCPClientIPsubnetMask OBJECT-TYPE
	SYNTAX	IpAddress
	ACCESS	read-only
	STATUS		mandatory
	DESCRIPTION
		"Wireless Access Point DHCP Client IP subnet mask
		If wirelessAPDHCPClientObtainIPchoice is set to static(0),
		then it should be the same as
		wirelessAPDHCPClientStaticIPsubnetMask."
	::= { wirelessAPIfSettingsGroup 3 }

wirelessAPDHCPClientGateway OBJECT-TYPE
	SYNTAX	IpAddress
	ACCESS	read-only
	STATUS		mandatory
	DESCRIPTION
		"Wireless Access Point DHCP Client gateway
		If wirelessAPDHCPClientObtainIPchoice is set to static(0),
		then it should be the same as
		wirelessAPDHCPClientStaticGateway."
	::= { wirelessAPIfSettingsGroup 4 }

wirelessAPDHCPClientPriDNS OBJECT-TYPE
	SYNTAX	IpAddress
	ACCESS	read-only
	STATUS		mandatory
	DESCRIPTION
		"Wireless Access Point DHCP Client primary DNS
		If wirelessAPDHCPClientObtainIPchoice is set to static(0),
		then it should be the same as
		wirelessAPDHCPClientStaticPriDNS."
	::= { wirelessAPIfSettingsGroup 5 }

wirelessAPDHCPClientSecDNS OBJECT-TYPE
	SYNTAX	IpAddress
	ACCESS	read-only
	STATUS		mandatory
	DESCRIPTION
		"Wireless Access Point DHCP Client secondary DNS
		If wirelessAPDHCPClientObtainIPchoice is set to static(0),
		then it should be the same as
		wirelessAPDHCPClientStaticSecDNS."
	::= { wirelessAPIfSettingsGroup 6 }

wirelessAPDHCPClientStaticIPaddr OBJECT-TYPE
	SYNTAX	IpAddress
	ACCESS	read-write
	STATUS		mandatory
	DESCRIPTION
		"Wireless Access Point DHCP Client static IP address
		If wirelessAPDHCPClientObtainIPchoice is set to automatic
		(1), then it should be 0.0.0.0."
	::= { wirelessAPIfSettingsGroup 7 }

wirelessAPDHCPClientStaticIPsubnetMask OBJECT-TYPE
	SYNTAX	IpAddress
	ACCESS	read-write
	STATUS		mandatory
	DESCRIPTION
		"Wireless Access Point DHCP Client static IP subnet mask
		If wirelessAPDHCPClientObtainIPchoice is set to automatic
		(1), then it should be 0.0.0.0."
	::= { wirelessAPIfSettingsGroup 8 }

wirelessAPDHCPClientStaticGateway OBJECT-TYPE
	SYNTAX	IpAddress
	ACCESS	read-write
	STATUS		mandatory
	DESCRIPTION
		"Wireless Access Point DHCP Client static gateway
		If wirelessAPDHCPClientObtainIPchoice is set to automatic
		(1), then it should be 0.0.0.0."
	::= { wirelessAPIfSettingsGroup 9 }

wirelessAPDHCPClientStaticPriDNS OBJECT-TYPE
	SYNTAX	IpAddress
	ACCESS	read-write
	STATUS		mandatory
	DESCRIPTION
		"Wireless Access Point DHCP Client static primary DNS
		If wirelessAPDHCPClientObtainIPchoice is set to automatic
		(1), then it should be 0.0.0.0."
	::= { wirelessAPIfSettingsGroup 10 }

wirelessAPDHCPClientStaticSecDNS OBJECT-TYPE
	SYNTAX	IpAddress
	ACCESS	read-write
	STATUS		mandatory
	DESCRIPTION
		"Wireless Access Point DHCP Client static secondary DNS
		If wirelessAPDHCPClientObtainIPchoice is set to automatic
		(1), then it should be 0.0.0.0."
	::= { wirelessAPIfSettingsGroup 11 }

wirelessAPName OBJECT-TYPE
	SYNTAX		DisplayString (SIZE(0..32))
	ACCESS		read-write
	STATUS		mandatory
	DESCRIPTION
		"Wireless Access Point Name"
	::= { wirelessAPIfSettingsGroup 12 }

wirelessAPWINSchoice OBJECT-TYPE
	SYNTAX	INTEGER {
				disAbled(0),
				enAbled(1)
			}
	ACCESS	read-write
	STATUS		mandatory
	DESCRIPTION
		"Wireless Access Point WINS choice
		If it is set to disAbled, then not using WINS."
	DEFVAL { 0}
 	::= { wirelessAPIfSettingsGroup 13 }

wirelessAPWINSServerName OBJECT-TYPE
	SYNTAX	DisplayString (SIZE(0..15))
	ACCESS		read-write
	STATUS		mandatory
	DESCRIPTION
		"WINS Server Name
		If wirelessAPWINSchoice is enAbled, either set this object
		If wirelessAPWINSchoice is disAbled, this object value
		should be cleared"
	::= { wirelessAPIfSettingsGroup 14 }



wirelessAPCountryDomain OBJECT-TYPE
	SYNTAX	INTEGER {
                none(0)
				africa(1),
				asia(2),
				australia(3),
				canada(4),
				europe(5),
				france(6),
				israel(7),
				japan(8),
				mexico(9),
				southAmerica(10),
				usa(11)
			}
	ACCESS	read-write
	STATUS		mandatory
	DESCRIPTION
		"Wireless Access Point Country Domain"
	::= { wirelessAPWirelessSettingsGroup 1 }

wirelessAPChannelNo OBJECT-TYPE
	SYNTAX	INTEGER(0..11)
	ACCESS	read-write
	STATUS		mandatory
	DESCRIPTION
		"Wireless Access Point Channel No
		Auto(0) default"
	DEFVAL { 11 }
	::= { wirelessAPWirelessSettingsGroup 2 }

wirelessAPSSID OBJECT-TYPE
	SYNTAX 	DisplayString (SIZE(0..32))
	ACCESS 	read-write
	STATUS 	mandatory
	DESCRIPTION
		"Wireless Access Point SSID
		This object value should be the same as
		IEEE 802.11 MIB dot11DesiredSSID"
	::= { wirelessAPWirelessSettingsGroup 3 }



wirelessAPPassphrase	OBJECT-TYPE
	SYNTAX	DisplayString (SIZE(1..32))
	ACCESS	read-write
	STATUS	mandatory
	DESCRIPTION
		"Wireless AP Passphrase

		This object won't be allowed to write unless wirelessAPWEPEnabled is enAbled"
	::= { wirelessAPWirelessSettingsGroup 7 }

wirelessAPGenerateKeysEnabled OBJECT-TYPE
	SYNTAX	INTEGER {
				disAbled(0),
				enAbled(1)
			}
	ACCESS	read-write
	STATUS	mandatory
	DESCRIPTION
		"Wireless Access Point Generate Keys

		This object won't be allowed to write unless wirelessAPWEPEnabled is enAbled"
	DEFVAL { 0 }
	::= { wirelessAPWirelessSettingsGroup 8 }

wirelessAPKeysSet OBJECT IDENTIFIER ::= { wirelessAPWirelessSettingsGroup 9 }

wirelessAPKeysSetTable	OBJECT-TYPE
	SYNTAX	SEQUENCE OF WirelessAPKeysSetEntry
	ACCESS	not-accessible
	STATUS		mandatory
	DESCRIPTION
		"Wireless Access Point Keys Set Table Object

		This object won't be allowed to write unless wirelessAPWEPEnabled is enAbled"
	::= { wirelessAPKeysSet 1 }

wirelessAPKeysSetEntry	OBJECT-TYPE
	SYNTAX	WirelessAPKeysSetEntry
	ACCESS	not-accessible
	STATUS		mandatory
	DESCRIPTION
		"An entry containing information for Wireless Access Point
		Keys Set Table"
	INDEX	{ wirelessAPKeysSetEnabled }
	::= { wirelessAPKeysSetTable 1 }

WirelessAPKeysSetEntry ::=
	SEQUENCE {
		wirelessAPKeysSetEnabled	INTEGER,
		wirelessAPKeys			DisplayString
	}

wirelessAPKeysSetEnabled OBJECT-TYPE
	SYNTAX	INTEGER {
				disAbled(0),
				enAbled(1)
			}
	ACCESS	read-write
	STATUS	mandatory
	DESCRIPTION
		"Enabled or Disabled a Wireless Access Point Key

		This object won't be allowed to write unless wirelessAPWEPEnabled is enAbled

		We only allow one key set will be enabled"
	DEFVAL { 0 }
	::= { wirelessAPKeysSetEntry 2 }

wirelessAPKeys	OBJECT-TYPE
	SYNTAX	OCTET STRING (SIZE(0..13))
	ACCESS	read-write
	STATUS	mandatory
	DESCRIPTION
		"Wireless AP Key
		This object won't be allowed to write unless wirelessAPWEPEnabled is enAbled"
	::= { wirelessAPKeysSetEntry 3 }

wirelessAPBasicRateChoice OBJECT-TYPE
	SYNTAX	INTEGER {
			auto(0),
			fixed(1)
			}
	ACCESS	read-write
	STATUS	mandatory
	DESCRIPTION
		"Wireless AP Basic Rate selection: auto(0) means
		Auto-negotiate and fixed(1) means Fixed rate"
	DEFVAL { 0 }
	::= { wirelessAPWirelessSettingsGroup 10 }




wirelessAPFixedRate OBJECT IDENTIFIER ::= {wirelessAPWirelessSettingsGroup 11}

wirelessAPFixedRate1 OBJECT-TYPE
	SYNTAX	INTEGER {
			oneM-disabled(0),
			oneM-enabled(1),
--            fixedRateNull(2)
			}
	ACCESS	read-write
	STATUS	mandatory
	DESCRIPTION
		"If wirelessAPBasicRateChoice is set to auto(0), then the
		value in this object should be empty.
		oneM means 1Mbps,
		twoM means 2Mbps,
		fiveDotfiveM means 5.5Mbps,
		elevenM means 11Mbps

		This object won't be allowed to write unless wirelessAPBasicRateChoice is set to fixed(1)"
	::= { wirelessAPFixedRate 1 }

wirelessAPFixedRate2 OBJECT-TYPE
	SYNTAX	INTEGER {
			twoM-disabled(0),
			twoM-enabled(1),
--            fixedRateNull(2)
			}
	ACCESS	read-write
	STATUS	mandatory
	DESCRIPTION
		"If wirelessAPBasicRateChoice is set to auto(0), then the
		value in this object should be empty.
		oneM means 1Mbps,
		twoM means 2Mbps,
		fiveDotfiveM means 5.5Mbps,
		elevenM means 11Mbps

		This object won't be allowed to write unless wirelessAPBasicRateChoice is set to fixed(1)"
	::= { wirelessAPFixedRate 2 }

wirelessAPFixedRate5-5 OBJECT-TYPE
	SYNTAX	INTEGER {
			fiveDotFiveM-disabled(0),
			fiveDotFiveM-enabled(1),
--            fixedRateNull(2)
			}
	ACCESS	read-write
	STATUS	mandatory
	DESCRIPTION
		"If wirelessAPBasicRateChoice is set to auto(0), then the
		value in this object should be empty.
		oneM means 1Mbps,
		twoM means 2Mbps,
		fiveDotfiveM means 5.5Mbps,
		elevenM means 11Mbps

		This object won't be allowed to write unless wirelessAPBasicRateChoice is set to fixed(1)"
	::= { wirelessAPFixedRate 3 }

wirelessAPFixedRate11 OBJECT-TYPE
	SYNTAX	INTEGER {
			elevenM-disabled(0),
			elevenM-enabled(1),
--            fixedRateNull(2)
			}
	ACCESS	read-write
	STATUS	mandatory
	DESCRIPTION
		"If wirelessAPBasicRateChoice is set to auto(0), then the
		value in this object should be empty.
		oneM means 1Mbps,
		twoM means 2Mbps,
		fiveDotfiveM means 5.5Mbps,
		elevenM means 11Mbps

		This object won't be allowed to write unless wirelessAPBasicRateChoice is set to fixed(1)"
	::= { wirelessAPFixedRate 4 }



wirelessAPRTSThreshold OBJECT-TYPE
	SYNTAX	INTEGER (0..2347)
      ACCESS	read-write
      STATUS 	mandatory
      DESCRIPTION
		"The value in this object should be the same as IEEE 802.11
		dot11RTSThreshold"
	::= { wirelessAPWirelessSettingsGroup 12 }

wirelessAPFragmentationThreshold OBJECT-TYPE
	SYNTAX	INTEGER (256..2346)
      ACCESS	read-write
      STATUS	mandatory
      DESCRIPTION
		"The value in this object should be the same as IEEE 802.11
		dot11FragmentationThreshold"
	::= { wirelessAPWirelessSettingsGroup 13 }

wirelessAPBeaconPeriod OBJECT-TYPE
	SYNTAX	INTEGER (1..65535)
	ACCESS	read-write
	STATUS	mandatory
	DESCRIPTION
		"The value in this object should be the same as IEEE 802.11
		dot11BeaconPeriod"
	::= { wirelessAPWirelessSettingsGroup 14 }



wirelessAPShortPreambleOptionImplemented OBJECT-TYPE
	SYNTAX 	INTEGER
    {
        short(0),
        long(1),
    }
	ACCESS 	read-write
	STATUS 	mandatory
	DESCRIPTION
    " The value of this object is 0	denoting that the short preamble used,
      1 denoting that the long preamble used."
	::= { wirelessAPWirelessSettingsGroup 15 }

wirelessAPAntennaSelection OBJECT-TYPE
	SYNTAX	INTEGER {
			primary(1),
			secondary(2),
			diversity(3)
			}
	ACCESS 	read-write
	STATUS 	mandatory
	DESCRIPTION
		"Antenna Selection"
	DEFVAL { 3 }
	::= { wirelessAPWirelessSettingsGroup 16 }

wirelessAPMaximumTransmitPowerLevel OBJECT-TYPE
	SYNTAX	INTEGER {
				eighteendbm(1),
				seventeendbm(2),
				fifteendbm(3),
				thirteendbm(4),
				sevendbm(5),
				zerodbm(6)
			}
	ACCESS 	read-write
	STATUS 	mandatory
	DESCRIPTION
		"The value in this object should be the same as IEEE 802.11
		dot11MaximumTransmitPowerLevel. However, our default value
		will be 18dbm.

		copy from IEEE 802.11 MIB:
		This attribute shall indicate the maximum transmit power,
		in dBm, allowed in the subband for the associated domain
		country string. The default value of this attribute shall
		be zero."
	DEFVAL { 1 }
	::= { wirelessAPWirelessSettingsGroup 17 }

wirelessAPOperatingMode OBJECT-TYPE
	SYNTAX	INTEGER {
				eight0twoDot1xAP(0),
				noneight0twoDot1xAP(1)
			}
	ACCESS 	read-write
	STATUS 	mandatory
	DESCRIPTION
		"Operating Mode"
	DEFVAL { 0 }
	::= { wirelessAPWirelessSettingsGroup 18 }

wirelessAPSSIDEnabled OBJECT-TYPE
	SYNTAX	INTEGER {
				disAbled(0),
				enAbled(1)
			}
	ACCESS	read-write
	STATUS	mandatory
	DESCRIPTION
		"Enabled or disabled Wireless Access Point Broadcast
		Wireless Network Name SSID"
	DEFVAL { 1 }
	::= { wirelessAPWirelessSettingsGroup 19 }


wirelessAP802dot1xSecurityEnabled OBJECT-TYPE
	SYNTAX	INTEGER {
				enAbled(0),
				disAbled(1)
			}
	ACCESS 	read-write
	STATUS 	mandatory
	DESCRIPTION
		"802.1x Security enabled or disabled"
	DEFVAL { 1 }
	::= { wirelessAPSecuritySettingsGroup 1 }


wirelessAPEAPauthType OBJECT-TYPE
	SYNTAX	INTEGER {
				NotAllowEAP-MD5(0),
				AllowEAP-MD5(1)
			}
	ACCESS 	read-write
	STATUS 	mandatory
	DESCRIPTION
		"Operating Mode
		This object won't be allowed to write unless wirelessAP802dot1xSecurityEnabled is enAbled"
	DEFVAL { 0 }
	::= { wirelessAPSecuritySettingsGroup 2 }


wirelessAPKeyExchange OBJECT-TYPE
	SYNTAX	INTEGER {
				disAbled(0),
				enAbled(1)
			}
	ACCESS 	read-write
	STATUS 	mandatory
	DESCRIPTION
		"AP Key Exchange enabled or disabled"
	DEFVAL { 1 }
	::= { wirelessAPSecuritySettingsGroup 16 }

wirelessAPKeyExchangeKeylife	OBJECT-TYPE
	SYNTAX	INTEGER (0..65535)
	ACCESS	read-write
	STATUS	mandatory
	DESCRIPTION
		"AP exchanged key lifetime"
	::= { wirelessAPSecuritySettingsGroup 17 }

wirelessAPRadiusServer	OBJECT-TYPE
	SYNTAX	DisplayString
	ACCESS	read-write
	STATUS	mandatory
	DESCRIPTION
		"Radius Server Name/IP Address"
	::= { wirelessAPSecuritySettingsGroup 3 }

wirelessAPRadiusPort	OBJECT-TYPE
	SYNTAX	INTEGER (0..65535)
	ACCESS	read-write
	STATUS	mandatory
	DESCRIPTION
		"Radius Port"
	::= { wirelessAPSecuritySettingsGroup 4 }

wirelessAPSharedKey	OBJECT-TYPE
	SYNTAX	DisplayString (SIZE(0..32))
	ACCESS	read-write
	STATUS	mandatory
	DESCRIPTION
		"Radius Server Shared Key"
	::= { wirelessAPSecuritySettingsGroup 5 }

wirelessAPRadiusServer2	OBJECT-TYPE
	SYNTAX	DisplayString
	ACCESS	read-write
	STATUS	mandatory
	DESCRIPTION
		"Radius Server Name/IP Address"
	::= { wirelessAPSecuritySettingsGroup 7 }



wirelessAPRadAccountPort	OBJECT-TYPE
	SYNTAX	INTEGER (0..65535)
	ACCESS	read-write
	STATUS	mandatory
	DESCRIPTION
		"Radius Accounting Port"
	::= { wirelessAPSecuritySettingsGroup 11 }



wirelessAPRadAccountEnable OBJECT-TYPE
	SYNTAX	INTEGER {
				disAbled(0),
				enAbled(1)
			}
	ACCESS 	read-write
	STATUS 	mandatory
	DESCRIPTION
		"AP Radius Accounting enabled or disabled"
	DEFVAL { 1 }
	::= { wirelessAPSecuritySettingsGroup 18 }



wirelessAPMacAuthEnable OBJECT-TYPE
	SYNTAX	INTEGER {
				disAbled(0),
				enAbled(1)
			}
	ACCESS 	read-write
	STATUS 	mandatory
	DESCRIPTION
		"AP Mac Authentication enabled or disabled"
	DEFVAL { 1 }
	::= { wirelessAPSecuritySettingsGroup 19 }


wirelessAPRadAccountUpdateEnable OBJECT-TYPE
	SYNTAX	INTEGER {
				disAbled(0),
				enAbled(1)
			}
	ACCESS 	read-write
	STATUS 	mandatory
	DESCRIPTION
		"AP Radius Account Update enabled or disabled"
	DEFVAL { 1 }
	::= { wirelessAPSecuritySettingsGroup 21 }


wirelessAPRadAccountUpdatePeriod	OBJECT-TYPE
	SYNTAX	INTEGER (0..65535)
	ACCESS	read-write
	STATUS	mandatory
	DESCRIPTION
		"AP Radius Account Update Period"
	::= { wirelessAPSecuritySettingsGroup 22 }


wirelessAPRadAccountIdlePeriod	OBJECT-TYPE
	SYNTAX	INTEGER (0..99)
	ACCESS	read-write
	STATUS	mandatory
	DESCRIPTION
		"Idle timer for AP not receiving any traffic from a wireless station to perform a dissociation"
	::= { wirelessAPSecuritySettingsGroup 23 }


wirelessTIOperateMode	OBJECT-TYPE
	SYNTAX	INTEGER {
    WirelessAccessPoint(0),
    Point-to-PointBridge(4),
    Point-to-Multi-PointBridge(5),
    ClientAccessPoint(3),
    RepeaterAccessPoint(2)
        }
	ACCESS	read-write
	STATUS	mandatory
	DESCRIPTION
		"AP Operation Mode"
	::= { wirelessAPSecuritySettingsGroup 25 }



wirelessTIDstMac OBJECT-TYPE
	SYNTAX		PhysAddress
	ACCESS		read-write
	STATUS		mandatory
	DESCRIPTION
		"The Destination Address When one operation mode is selected which the remote address necessary."
	::= { wirelessAPSecuritySettingsGroup 26 }



wirelessTIIsolation	OBJECT-TYPE
	SYNTAX	INTEGER {
    off(0),
    on(1)
        }
	ACCESS	read-write
	STATUS	mandatory
	DESCRIPTION
		"AP Wireless Separation Setting"
	::= { wirelessAPSecuritySettingsGroup 28 }



wirelessTIEnable80211d	OBJECT-TYPE
	SYNTAX	INTEGER {
    off(0),
    on(1)
        }
	ACCESS	read-write
	STATUS	mandatory
	DESCRIPTION
		"AP Worldwide Mode Setting"
	::= { wirelessAPSecuritySettingsGroup 29 }

--wirelessAPWPARebootLog	OBJECT-TYPE
--	SYNTAX	INTEGER {
--    Disable(0),
--    Enable(1)
--        }
--	ACCESS	read-write
--	STATUS	mandatory
--	DESCRIPTION
--		"WPA Reboot Log"
--	::= { wirelessAPSecuritySettingsGroup 35 }

--wirelessAPWPAPSK	OBJECT-TYPE
--	SYNTAX	DisplayString (SIZE(0..32))
--	ACCESS	read-write
--	STATUS	mandatory
--	DESCRIPTION
--		"WPA PSK"
--	::= { wirelessAPSecuritySettingsGroup 36 }

wirelessAPSecurityMode  OBJECT-TYPE
	SYNTAX	INTEGER {

    OPEN-DISABLE-MODE(0),
    OPEN-64WEP-MODE(1),
    OPEN-128WEP-MODE(2),
    SHARED-64WEP-MODE(3),
    SHARED-128WEP-MODE(4)
--    WPA-TKIP-MODE(5),
--    WPA-TKIP-64WEP-MODE(6),
--    WPA-TKIP-128WEP-MODE(7),
--    WPA-PSK-TKIP-MODE(8),
--    WPA-PSK-TKIP-64WEP-MODE(9),
--    WPA-PSK-TKIP-128WEP-MODE(10)
        }
	ACCESS	read-write
	STATUS	mandatory
	DESCRIPTION
		"AP Security Mode Setting, can take the place of AP Authentication and Encryption Setting Logic Relation."
	::= { wirelessAPSecuritySettingsGroup 37 }


END
