FSM7326-QOS-MIB DEFINITIONS ::= BEGIN

-- Copyright 2003 LVL7 Systems, Inc.  All rights reserved.

-- This SNMP Management Information Specification
-- embodies LVL7 System's confidential and proprietary
-- intellectual property.  LVL7 Systems retains all title
-- and ownership in the Specification including any revisions.

-- This Specification is supplied "AS IS", LVL7 Systems
-- makes no warranty, either expressed or implied,
-- as to the use, operation, condition, or performance of the
-- Specification.

    IMPORTS
      MODULE-IDENTITY, OBJECT-TYPE, NOTIFICATION-TYPE,
      Integer32, Gauge32                                FROM SNMPv2-SMI
      RowStatus                                         FROM SNMPv2-TC
      fsm7326                                           FROM FSM7326-REF-MIB
      DisplayString                                     FROM RFC1213-MIB;

    fsm7326QOS MODULE-IDENTITY
           LAST-UPDATED "200311101200Z" -- 10 Nov 2003 12:00:00 GMT
    ORGANIZATION "Netgear"

    CONTACT-INFO
        ""
    DESCRIPTION
        ""
-- revision history
    REVISION
        "200311101200Z" -- 10 Nov 2003 12:00:00 GMT

    DESCRIPTION
        "Initial revision."
    ::= { fsm7326 3 }

END
