MOTOROLA-PTP-MIB DEFINITIONS ::= BEGIN

   IMPORTS
      IpAddress, Counter, Gauge, TimeTicks, NetworkAddress, enterprises
         FROM RFC1155-SMI
      OBJECT-TYPE
         FROM RFC-1212
      DisplayString, PhysAddress
         FROM SNMPv2-TC
      NOTIFICATION-TYPE
         FROM SNMPv2-SMI;

   -- Define the Motorola PTP object identifier
   motorola           OBJECT IDENTIFIER ::= { enterprises 17713 }

   -- Groups in motorola
   ptp                OBJECT IDENTIFIER ::= { motorola 1 }
   ptmp               OBJECT IDENTIFIER ::= { motorola 2 }

   -- Groups in ptp
   configuration      OBJECT IDENTIFIER ::= { ptp 5 }
   licence            OBJECT IDENTIFIER ::= { ptp 8 }
   mgmt               OBJECT IDENTIFIER ::= { ptp 9 }
   phyControl         OBJECT IDENTIFIER ::= { ptp 10 }
   phyStatus          OBJECT IDENTIFIER ::= { ptp 12 }
   reset              OBJECT IDENTIFIER ::= { ptp 18 }
   versions           OBJECT IDENTIFIER ::= { ptp 19 }
   pubStats           OBJECT IDENTIFIER ::= { ptp 20 }
   encryption         OBJECT IDENTIFIER ::= { ptp 22 }
   ptpTraps           OBJECT IDENTIFIER ::= { ptp 99 }

   -- Configuration group attribute definitions
   --
   iPAddress OBJECT-TYPE
      SYNTAX IpAddress
      ACCESS read-only
      STATUS mandatory
      DESCRIPTION
             "Internet protocol (IP) address. This address is used by
             the family of Internet protocols to uniquely this
             identify the unit on a network"
      ::= { configuration 1 }

   subnetMask OBJECT-TYPE
      SYNTAX IpAddress
      ACCESS read-only
      STATUS mandatory
      DESCRIPTION
             "A subnet allows the flow of network traffic between
             hosts to be segregated based on a network
             configuration. By organizing hosts into
             logical groups, subnetting can improve network
             security and performance"
      ::= { configuration 2 }

   gatewayIPAddress OBJECT-TYPE
      SYNTAX IpAddress
      ACCESS read-only
      STATUS mandatory
      DESCRIPTION
             "The IP address of a computer on the current network that
             is currently acting as a network gateway. A gateway
             acts as an entrance / exit to packets from / to
             other networks"
      ::= { configuration 3 }

   targetMACAddress OBJECT-TYPE
      SYNTAX OCTET STRING (SIZE(6))
      ACCESS read-only
      STATUS mandatory
      DESCRIPTION
             "MAC address of the PTP wireless unit forming the other
             end of the PTP link"
      ::= { configuration 4 }

   masterSlaveMode OBJECT-TYPE
      SYNTAX INTEGER {
                       master(0),
                       slave(1)
                     }
      ACCESS read-only
      STATUS mandatory
      DESCRIPTION
             "The PTP wireless link operates using a master and slave
             relationship"
      ::= { configuration 5 }

   maximumTransmitPower OBJECT-TYPE
      SYNTAX INTEGER (-15..25)
      ACCESS read-only
      STATUS mandatory
      DESCRIPTION
             "Maximum transmit power the wireless unit is permitted to
             use when establishing and maintaining the wireless
             link"
      ::= { configuration 6 }

   -- Licence group attribute definitions
   --
   regionCode OBJECT-TYPE
      SYNTAX INTEGER (0..31)
      ACCESS read-only
      STATUS mandatory
      DESCRIPTION
             "The region code prohibits the wireless unit from
             operating outside the regulated limits"
      ::= { licence 1 }

   productVariant OBJECT-TYPE
      SYNTAX INTEGER {
                       motorola-ptp-xx400-full(0),
                       motorola-ptp-xx400-full(1),
                       motorola-ptp-xx400-full(2),
                       motorola-ptp-xx400-lite(3),
                       spare-1(4),
                       spare-2(5),
                       spare-3(6),
                       spare-4(7),
                       spare-5(8),
                       spare-6(9),
                       spare-7(10),
                       motorola-ptp-xx600-lite(11),
                       motorola-ptp-xx600-full(12)
                     }
      ACCESS read-only
      STATUS mandatory
      DESCRIPTION
             "The product variant"
      ::= { licence 2 }

   productName OBJECT-TYPE
      SYNTAX DisplayString (SIZE(0..255))
      ACCESS read-only
      STATUS mandatory
      DESCRIPTION
             "Name of the product variant"
      ::= { licence 3 }

   ethernetFibreSupport OBJECT-TYPE
      SYNTAX INTEGER {
                       disabled(0),
                       enabled(1)
                     }
      ACCESS read-only
      STATUS mandatory
      DESCRIPTION
             "Gigabit Ethernet fibre support"
      ::= { licence 4 }

   frequencyVariant OBJECT-TYPE
      SYNTAX INTEGER {
                       freq-5800-mhz(0),
                       freq-5400-mhz(1),
                       freq-4900-mhz(2)
                     }
      ACCESS read-only
      STATUS mandatory
      DESCRIPTION
             "Frequency variant of the wireless unit"
      ::= { licence 5 }

   -- Mgmt group attribute definitions
   --
   targetRange OBJECT-TYPE
      SYNTAX INTEGER (0..2000)
      ACCESS read-only
      STATUS mandatory
      DESCRIPTION
             "Initial target range used in installation +/-1,
             expressed in tenths of a kilometer. When
             Auto-Ranging this must be set to 0"
      ::= { mgmt 1 }

   rangingMode OBJECT-TYPE
      SYNTAX INTEGER {
                       auto-0-5-km(0),
                       auto-0-40-km(1),
                       auto-0-100-km(2),
                       auto-0-200-km(3),
                       target-range(4)
                     }
      ACCESS read-only
      STATUS mandatory
      DESCRIPTION
             "Type of ranging to use during installation, either
             Auto-Ranging or use a selectable Target
             Range"
      ::= { mgmt 2 }

   -- PhyControl group attribute definitions
   --
   asymmetricTDD OBJECT-TYPE
      SYNTAX INTEGER {
                       symmetric-data-rate-1-to-1(0),
                       asymmetric-data-rate-2-to-1(1),
                       prohibited(2),
                       latency-optimised(3)
                     }
      ACCESS read-only
      STATUS mandatory
      DESCRIPTION
             "Control TDD Structure"
      ::= { phyControl 1 }

   -- PhyStatus group attribute definitions
   --
   receivePower OBJECT-TYPE
      SYNTAX INTEGER
      ACCESS read-only
      STATUS mandatory
      DESCRIPTION
             "Receive power expressed in tenths of a dBm"
      ::= { phyStatus 1 }

   vectorError OBJECT-TYPE
      SYNTAX INTEGER
      ACCESS read-only
      STATUS mandatory
      DESCRIPTION
             "The vector error measurement compares the received
             signal's IQ modulation characteristics to an
             ideal signal to determine the composite error
             vector magnitude. The value represented by this
             attribute is the average vector error over the
             previous second expressed in tenths of a dB"
      ::= { phyStatus 2 }

   transmitPower OBJECT-TYPE
      SYNTAX INTEGER
      ACCESS read-only
      STATUS mandatory
      DESCRIPTION
             "Transmit power expressed in tenths of a dBm"
      ::= { phyStatus 3 }

   range OBJECT-TYPE
      SYNTAX INTEGER
      ACCESS read-only
      STATUS mandatory
      DESCRIPTION
             "Distance between the two peer wireless units expressed
             in tenths of a kilometer"
      ::= { phyStatus 4 }

   linkLoss OBJECT-TYPE
      SYNTAX INTEGER (-500..500)
      ACCESS read-only
      STATUS mandatory
      DESCRIPTION
             "The wireless link loss expressed in tenths of a dB"
      ::= { phyStatus 5 }

   receiveChannel OBJECT-TYPE
      SYNTAX INTEGER (0..21)
      ACCESS read-only
      STATUS mandatory
      DESCRIPTION
             "Current active receive channel"
      ::= { phyStatus 6 }

   transmitChannel OBJECT-TYPE
      SYNTAX INTEGER (0..21)
      ACCESS read-only
      STATUS mandatory
      DESCRIPTION
             "Current active transmit channel"
      ::= { phyStatus 7 }

   receiveModulationMode OBJECT-TYPE
      SYNTAX INTEGER {
                       mod-acquisition(0),
                       mod-bpsk-1-2(1),
                       mod-qpsk-1-2(2),
                       mod-qpsk-2-3(3),
                       mod-16qam-1-2(4),
                       mod-16qam-3-4(5),
                       mod-64qam-2-3(6),
                       mod-64qam-3-4(7),
                       mod-64qam-7-8(8)
                     }
      ACCESS read-only
      STATUS mandatory
      DESCRIPTION
             "Current active receive modulation mode"
      ::= { phyStatus 8 }

   transmitModulationMode OBJECT-TYPE
      SYNTAX INTEGER {
                       mod-acquisition(0),
                       mod-bpsk-1-2(1),
                       mod-qpsk-1-2(2),
                       mod-qpsk-2-3(3),
                       mod-16qam-1-2(4),
                       mod-16qam-3-4(5),
                       mod-64qam-2-3(6),
                       mod-64qam-3-4(7),
                       mod-64qam-7-8(8)
                     }
      ACCESS read-only
      STATUS mandatory
      DESCRIPTION
             "Current active transmit modulation mode"
      ::= { phyStatus 9 }

   receiveFreq OBJECT-TYPE
      SYNTAX INTEGER (0..5875)
      ACCESS read-only
      STATUS mandatory
      DESCRIPTION
             "Current receive frequency expressed in MHz"
      ::= { phyStatus 11 }

   transmitFreq OBJECT-TYPE
      SYNTAX INTEGER (0..5875)
      ACCESS read-only
      STATUS mandatory
      DESCRIPTION
             "Current transmit frequency expressed in MHz"
      ::= { phyStatus 12 }

   signalStrengthRatio OBJECT-TYPE
      SYNTAX INTEGER
      ACCESS read-only
      STATUS mandatory
      DESCRIPTION
             "Signal strength ratio (Vertical / Horizontal) expressed
             in tenths of a dB"
      ::= { phyStatus 13 }

   -- Reset group attribute definitions
   --
   systemReset OBJECT-TYPE
      SYNTAX INTEGER {
                       running(0),
                       console-reboot(1)
                     }
      ACCESS read-write
      STATUS mandatory
      DESCRIPTION
             "Setting this attribute to '1' will cause a system
             reboot"
      ::= { reset 1 }

   -- Versions group attribute definitions
   --
   softwareVersion OBJECT-TYPE
      SYNTAX DisplayString (SIZE(0..255))
      ACCESS read-only
      STATUS mandatory
      DESCRIPTION
             "Current software version"
      ::= { versions 1 }

   hardwareVersion OBJECT-TYPE
      SYNTAX DisplayString (SIZE(0..255))
      ACCESS read-only
      STATUS mandatory
      DESCRIPTION
             "Hardware platform version"
      ::= { versions 2 }

   secondarySoftwareVersion OBJECT-TYPE
      SYNTAX DisplayString (SIZE(0..255))
      ACCESS read-only
      STATUS mandatory
      DESCRIPTION
             "Secondary software version, used when the primary
             software image is invalid or erased"
      ::= { versions 3 }

   bootVersion OBJECT-TYPE
      SYNTAX DisplayString (SIZE(0..255))
      ACCESS read-only
      STATUS mandatory
      DESCRIPTION
             "Boot code software version"
      ::= { versions 4 }

   -- PubStats group attribute definitions
   --
   receiveDataRate OBJECT-TYPE
      SYNTAX INTEGER
      ACCESS read-only
      STATUS mandatory
      DESCRIPTION
             "Average data rate over the last one second interval
             expressed in kbps"
      ::= { pubStats 1 }

   transmitDataRate OBJECT-TYPE
      SYNTAX INTEGER
      ACCESS read-only
      STATUS mandatory
      DESCRIPTION
             "Average data rate over the last one second interval
             expressed in kbps"
      ::= { pubStats 2 }

   aggregateDataRate OBJECT-TYPE
      SYNTAX INTEGER
      ACCESS read-only
      STATUS mandatory
      DESCRIPTION
             "Average data rate over the last one second interval
             expressed in kbps"
      ::= { pubStats 3 }

   -- Encryption group attribute definitions
   --
   encryptionAlgorithm OBJECT-TYPE
      SYNTAX INTEGER {
                       none(0),
                       aes-rijndael(1),
                       aes-256-bit-rijndael(2)
                     }
      ACCESS read-only
      STATUS mandatory
      DESCRIPTION
             "The Encryption Algorithm used by the wireless link. You
             should be aware that enabling encryption results
             in a reduction in available data bandwidth N.B. The
             same Encryption Algorithm must be configured at BOTH
             ends of the link for it to function correctly"
      ::= { encryption 1 }

   -- Enterprise NOTIFICATION definitions
   --
   dfsChannelChangeTrap NOTIFICATION-TYPE
      OBJECTS { receiveChannel }
      STATUS current
      DESCRIPTION "DFS channel change event"
      ::= { ptpTraps 1 }

   dfsImpulsiveInterferenceDetectedTrap NOTIFICATION-TYPE
      OBJECTS { receiveChannel }
      STATUS current
      DESCRIPTION "DFS impulsive interference detected event"
      ::= { ptpTraps 2 }
   END
