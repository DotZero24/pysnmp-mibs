--
--       whisp-plv-modem.mib
--
--      **********************************************************************************
--       Copyright 2006 (c) , Motorola, Inc.
--       Motorola Confidential Proprietary
--      **********************************************************************************
--
--       This module contains registrations for Canopy related items such
--       as the identity of products, product components and other MIB
--       related items.
--
--      **********************************************************************************
--       Revision History:
--
--       <Date>                  <Author>                <Changes>
--       04/04/2006             Balaji G V               Initial release.
--       05/07/2007             Balaji G V               Added Repeater Configuration
--                                                       Group
--       07/07/2007             Balaji G V               Added VLAN Configuration Group
--      **********************************************************************************
WHISP-PLV-MODEM-MIB DEFINITIONS ::= BEGIN

IMPORTS
        MODULE-IDENTITY, OBJECT-TYPE, NOTIFICATION-TYPE,
        Integer32, IpAddress
                FROM SNMPv2-SMI
        DisplayString, MacAddress
                FROM SNMPv2-TC
        OBJECT-GROUP, NOTIFICATION-GROUP, MODULE-COMPLIANCE
                FROM SNMPv2-CONF
        whispPlvModem
                FROM WHISP-GLOBAL-REG-MIB;

whispPlvModemMIB MODULE-IDENTITY
        LAST-UPDATED "200604041030Z"    -- Apr 04, 2006 10:30:00 AM
        ORGANIZATION "Motorola"
        CONTACT-INFO
                     "Canopy Technical Support
		     email: technical-support@canopywireless.com"
        DESCRIPTION  "Initial Version."
        REVISION     "200604041030Z"     -- Apr 04, 2006 10:30:00 AM
        DESCRIPTION
                "Initial version."
        ::= { whispPlvModem 1 }


-- Scalars and Tables
--

whispPlvModemObjects OBJECT IDENTIFIER
        ::= { whispPlvModemMIB 1 }

-- Modem Info
--

whispPlvModemInfo OBJECT IDENTIFIER
        ::= { whispPlvModemObjects 1 }

modemInfoModel OBJECT-TYPE
        SYNTAX  DisplayString (SIZE (0..255))
        MAX-ACCESS read-only
        STATUS current
        DESCRIPTION
                "This object indicates the Modem Model Number."
        ::= { whispPlvModemInfo 1 }

modemInfoSerialNumber OBJECT-TYPE
        SYNTAX  DisplayString (SIZE (0..255))
        MAX-ACCESS read-only
        STATUS current
        DESCRIPTION
                "This object indicates the Modem Serial Number."
        ::= { whispPlvModemInfo 2 }

modemInfoDeviceMac OBJECT-TYPE
        SYNTAX  MacAddress
        MAX-ACCESS read-only
        STATUS current
        DESCRIPTION
                "This object indicates the Modem Device MAC Address."
        ::= { whispPlvModemInfo 3 }

modemInfoPlcMac OBJECT-TYPE
        SYNTAX  MacAddress
        MAX-ACCESS read-only
        STATUS current
        DESCRIPTION
                "This object indicates the Modem PLC MAC Address"
        ::= { whispPlvModemInfo 4 }

modemInfoHardwareVer OBJECT-TYPE
        SYNTAX  DisplayString (SIZE (0..255))
        MAX-ACCESS read-only
        STATUS current
        DESCRIPTION
                "This object indicates the Modem Hardware Version."
        ::= { whispPlvModemInfo 5 }

modemInfoDeviceFirmwareVer OBJECT-TYPE
        SYNTAX  DisplayString (SIZE (0..255))
        MAX-ACCESS read-only
        STATUS current
        DESCRIPTION
                "This object indicates the Modem Firmware Version."
        ::= { whispPlvModemInfo 6 }

modemInfoBootLoaderVer OBJECT-TYPE
        SYNTAX  DisplayString (SIZE (0..255))
        MAX-ACCESS read-only
        STATUS current
        DESCRIPTION
                "This object indicates the Modem Boot Loader Version."
        ::= { whispPlvModemInfo 7 }

modemInfoSimFirmwareVer OBJECT-TYPE
        SYNTAX  DisplayString (SIZE (0..255))
        MAX-ACCESS read-only
        STATUS current
        DESCRIPTION
                "This object indicates the Intellon Simple Module Firmware Version."
        ::= { whispPlvModemInfo 8 }

modemInfoDeviceUpgradeStatus OBJECT-TYPE
        SYNTAX  INTEGER {
                        notStarted(1),
                        inProgress(2),
                        failed(3),
                        successful(4) }
        MAX-ACCESS read-only
        STATUS current
        DESCRIPTION
                "This object indicates the Modems last Software Upgrade Status.
                 1 - Upgrade not started
                 2 - Upgrade in progress
                 3 - Last Upgrade failed
                 4 - Last Upgrade was successful."
        ::= { whispPlvModemInfo 9 }

modemInfoSimUpgradeStatus OBJECT-TYPE
        SYNTAX  INTEGER {
                        notStarted(1),
                        inProgress(2),
                        failed(3),
                        successful(4) }
        MAX-ACCESS read-only
        STATUS current
        DESCRIPTION
                "This object indicates the Intellon Simple Module Firmware Upgrade Status.
                 1 - Upgrade not started
                 2 - Upgrade in progress
                 3 - Last Upgrade failed
                 4 - Last Upgrade was successful."
        ::= { whispPlvModemInfo 10 }

modemInfoCurrentMode OBJECT-TYPE
        SYNTAX  INTEGER {
                        bridge(1),
                        nat(2) }
        MAX-ACCESS read-only
        STATUS current
        DESCRIPTION
                "This object indicates the current operating mode of the Modem.
                 1 - Bridge Mode
                 2 - NAT Mode."
        ::= { whispPlvModemInfo 11 }

modemInfoActiveBandwidthConfig OBJECT-TYPE
        SYNTAX  INTEGER {
                        configured(1),
                        provisioned(2) }
        MAX-ACCESS read-only
        STATUS current
        DESCRIPTION
                "This object indicates if the Active Bandwidth settings are either Configured
                 OR Provisioned. "
        ::= { whispPlvModemInfo 12 }

modemInfoActiveUpLinkBandwidth OBJECT-TYPE
        SYNTAX  INTEGER {
                        fullSpeed(1),
                        u64Kbps(2),
                        u128Kbps(3),
                        u256Kbps(4),
                        u512Kbps(5),
                        u1Mbps(6),
                        u4Mbps(7),
                        u10Mbps(8) }
        MAX-ACCESS read-only
        STATUS current
        DESCRIPTION
                "This object indicates if the Active Bandwidth settings are either Configured
                 OR Provisioned. "
        ::= { whispPlvModemInfo 13 }

modemInfoActiveDownLinkBandwidth OBJECT-TYPE
        SYNTAX  INTEGER {
                        fullSpeed(1),
                        d64Kbps(2),
                        d128Kbps(3),
                        d256Kbps(4),
                        d512Kbps(5),
                        d1Mbps(6),
                        d4Mbps(7),
                        d10Mbps(8) }
        MAX-ACCESS read-only
        STATUS current
        DESCRIPTION
                "This object indicates if the Active Bandwidth settings are either Configured
                 OR Provisioned. "
        ::= { whispPlvModemInfo 14 }

-- Modem Configuration
--

whispPlvModemConfig OBJECT IDENTIFIER
        ::= { whispPlvModemObjects 2 }

modemConfPacketPriorityConfig OBJECT-TYPE
        SYNTAX  INTEGER {
                        fixedQoS(1),
                        tos(2) }
        MAX-ACCESS read-write
        STATUS current
        DESCRIPTION
                "This object is used to configure 802.1p Packet Priority type.
                 1 - Fixed QoS
                 2 - QoS Based on ToS."
        DEFVAL { 1 }
        ::= { whispPlvModemConfig 1 }

modemConfFixedQoSConfig OBJECT-TYPE
        SYNTAX  INTEGER {
                        default(1),
                        background(2),
                        bestEffort(3),
                        excellentEffort(4),
                        controlLoad(5),
                        videoOrAudio(6),
                        voice(7),
                        networkControl(8) }
        MAX-ACCESS read-write
        STATUS current
        DESCRIPTION
                "This object is used to configure Fixed QoS type."
        DEFVAL { default }
        ::= { whispPlvModemConfig 2 }

modemConfUpLinkDataRate OBJECT-TYPE
        SYNTAX  INTEGER {
                        fullSpeed(1),
                        u64Kbps(2),
                        u128Kbps(3),
                        u256Kbps(4),
                        u512Kbps(5),
                        u1Mbps(6),
                        u4Mbps(7),
                        u10Mbps(8) }
        MAX-ACCESS read-write
        STATUS current
        DESCRIPTION
                "This object is used to configure Uplink Data Rate."
        DEFVAL { fullSpeed }
        ::= { whispPlvModemConfig 3 }

modemConfDownLinkDataRate OBJECT-TYPE
        SYNTAX  INTEGER {
                        fullSpeed(1),
                        d64Kbps(2),
                        d128Kbps(3),
                        d256Kbps(4),
                        d512Kbps(5),
                        d1Mbps(6),
                        d4Mbps(7),
                        d10Mbps(8) }
        MAX-ACCESS read-write
        STATUS current
        DESCRIPTION
                "This object is used to configure Downlink Data Rate."
        DEFVAL { fullSpeed }
        ::= { whispPlvModemConfig 4 }

modemConfPSD OBJECT-TYPE
        SYNTAX  OCTET STRING (SIZE (84))
        MAX-ACCESS read-write
        STATUS current
        DESCRIPTION
                "This object indicates the Power Spectral Density of the signal, at
                 all the 84 carriers, that the device transmits. Starting at the left most octet,
                 which represents the spectral value at channel number 0, each octet represents the
                 spectral value at the corresponding channel number.
                 The channel numbers 4, 5, 13, 14, 29, 49, 50, 51, 69 and 70 are masked and their
                 spectral values cannot be changed."
        ::= { whispPlvModemConfig 5 }

modemConfUpLinkMir OBJECT-TYPE
        SYNTAX  Integer32
        UNITS "Kilobits/sec"
        MAX-ACCESS read-write
        STATUS current
        DESCRIPTION
                "This object is used to configure Uplink Maximum Information Rate.
                 This object is for configuring the Data Rate in Kbps, instead of enumerations,
                 as in 'modemConfUpLinkDataRate'. If this object is configured to a Data Rate, which
                 is not supported by the Modem, it will be internally converted to the nearest higher
                 value supported by the Modem. Modem supports only the following Data Rates:
                 64Kbps, 128Kbps, 256Kbps, 512Kbps, 1Mbps, 4Mbps, 10Mbps and 85Mbps(Full Speed)."
        ::= { whispPlvModemConfig 6 }

modemConfDownLinkMir OBJECT-TYPE
        SYNTAX  Integer32
        UNITS "Kilobits/sec"
        MAX-ACCESS read-write
        STATUS current
        DESCRIPTION
                "This object is used to configure Downlink Maximum Information Rate.
                 This object is for configuring the Data Rate in Kbps, instead of enumerations,
                 as in 'modemConfDownLinkDataRate'. If this object is configured to a Data Rate, which
                 is not supported by the Modem, it will be internally converted to the nearest higher
                 value supported by the Modem. Modem supports only the following Data Rates:
                 64Kbps, 128Kbps, 256Kbps, 512Kbps, 1Mbps, 4Mbps, 10Mbps and 85Mbps(Full Speed)"
        ::= { whispPlvModemConfig 7 }

-- Modem SNMP Traps Configuration
--

whispPlvModemTrapConfig OBJECT IDENTIFIER
        ::= { whispPlvModemObjects 3 }

modemConfTrapIp1 OBJECT-TYPE
        SYNTAX  IpAddress
        MAX-ACCESS read-write
        STATUS current
        DESCRIPTION
                "This object is used to configure IP Address of SNMP Trap Client #1."
        ::= { whispPlvModemTrapConfig 1 }

modemConfTrapCommStr1 OBJECT-TYPE
        SYNTAX  DisplayString (SIZE (0..255))
        MAX-ACCESS read-write
        STATUS current
        DESCRIPTION
                "This object is used to configure SNMP CommStrunity string for Trap Client #1."
        ::= { whispPlvModemTrapConfig 2 }

modemConfTrapIp2 OBJECT-TYPE
        SYNTAX  IpAddress
        MAX-ACCESS read-write
        STATUS current
        DESCRIPTION
                "This object is used to configure IP Address of SNMP Trap Client #2."
        ::= { whispPlvModemTrapConfig 3 }

modemConfTrapCommStr2 OBJECT-TYPE
        SYNTAX  DisplayString (SIZE (0..255))
        MAX-ACCESS read-write
        STATUS current
        DESCRIPTION
                "This object is used to configure SNMP CommStrunity string for Trap Client #2."
        ::= { whispPlvModemTrapConfig 4 }

modemConfTrapIp3 OBJECT-TYPE
        SYNTAX  IpAddress
        MAX-ACCESS read-write
        STATUS current
        DESCRIPTION
                "This object is used to configure IP Address of SNMP Trap Client #3."
        ::= { whispPlvModemTrapConfig 5 }

modemConfTrapCommStr3 OBJECT-TYPE
        SYNTAX  DisplayString (SIZE (0..255))
        MAX-ACCESS read-write
        STATUS current
        DESCRIPTION
                "This object is used to configure SNMP CommStrunity string for Trap Client #3."
        ::= { whispPlvModemTrapConfig 6 }

modemConfTrapIp4 OBJECT-TYPE
        SYNTAX  IpAddress
        MAX-ACCESS read-write
        STATUS current
        DESCRIPTION
                "This object is used to configure IP Address of SNMP Trap Client #4."
        ::= { whispPlvModemTrapConfig 7 }

modemConfTrapCommStr4 OBJECT-TYPE
        SYNTAX  DisplayString (SIZE (0..255))
        MAX-ACCESS read-write
        STATUS current
        DESCRIPTION
                "This object is used to configure SNMP CommStrunity string for Trap Client #4."
        ::= { whispPlvModemTrapConfig 8 }

modemConfTrapIp5 OBJECT-TYPE
        SYNTAX  IpAddress
        MAX-ACCESS read-write
        STATUS current
        DESCRIPTION
                "This object is used to configure IP Address of SNMP Trap Client #5."
        ::= { whispPlvModemTrapConfig 9 }

modemConfTrapCommStr5 OBJECT-TYPE
        SYNTAX  DisplayString (SIZE (0..255))
        MAX-ACCESS read-write
        STATUS current
        DESCRIPTION
                "This object is used to configure SNMP CommStrunity string for Trap Client #5."
        ::= { whispPlvModemTrapConfig 10 }

modemConfTrapIp6 OBJECT-TYPE
        SYNTAX  IpAddress
        MAX-ACCESS read-write
        STATUS current
        DESCRIPTION
                "This object is used to configure IP Address of SNMP Trap Client #6."
        ::= { whispPlvModemTrapConfig 11 }

modemConfTrapCommStr6 OBJECT-TYPE
        SYNTAX  DisplayString (SIZE (0..255))
        MAX-ACCESS read-write
        STATUS current
        DESCRIPTION
                "This object is used to configure SNMP CommStrunity string for Trap Client #6."
        ::= { whispPlvModemTrapConfig 12 }

modemConfTrapIp7 OBJECT-TYPE
        SYNTAX  IpAddress
        MAX-ACCESS read-write
        STATUS current
        DESCRIPTION
                "This object is used to configure IP Address of SNMP Trap Client #7."
        ::= { whispPlvModemTrapConfig 13 }

modemConfTrapCommStr7 OBJECT-TYPE
        SYNTAX  DisplayString (SIZE (0..255))
        MAX-ACCESS read-write
        STATUS current
        DESCRIPTION
                "This object is used to configure SNMP CommStrunity string for Trap Client #7."
        ::= { whispPlvModemTrapConfig 14 }

modemConfTrapIp8 OBJECT-TYPE
        SYNTAX  IpAddress
        MAX-ACCESS read-write
        STATUS current
        DESCRIPTION
                "This object is used to configure IP Address of SNMP Trap Client #8."
        ::= { whispPlvModemTrapConfig 15 }

modemConfTrapCommStr8 OBJECT-TYPE
        SYNTAX  DisplayString (SIZE (0..255))
        MAX-ACCESS read-write
        STATUS current
        DESCRIPTION
                "This object is used to configure SNMP CommStrunity string for Trap Client #8."
        ::= { whispPlvModemTrapConfig 16 }

modemConfTrapIp9 OBJECT-TYPE
        SYNTAX  IpAddress
        MAX-ACCESS read-write
        STATUS current
        DESCRIPTION
                "This object is used to configure IP Address of SNMP Trap Client #9."
        ::= { whispPlvModemTrapConfig 17 }

modemConfTrapCommStr9 OBJECT-TYPE
        SYNTAX  DisplayString (SIZE (0..255))
        MAX-ACCESS read-write
        STATUS current
        DESCRIPTION
                "This object is used to configure SNMP CommStrunity string for Trap Client #9."
        ::= { whispPlvModemTrapConfig 18 }

modemConfTrapIp10 OBJECT-TYPE
        SYNTAX  IpAddress
        MAX-ACCESS read-write
        STATUS current
        DESCRIPTION
                "This object is used to configure IP Address of SNMP Trap Client #10."
        ::= { whispPlvModemTrapConfig 19 }

modemConfTrapCommStr10 OBJECT-TYPE
        SYNTAX  DisplayString (SIZE (0..255))
        MAX-ACCESS read-write
        STATUS current
        DESCRIPTION
                "This object is used to configure SNMP CommStrunity string for Trap Client #10."
        ::= { whispPlvModemTrapConfig 20 }

-- Modem Admin Configuration
--

whispPlvModemAdmConfig OBJECT IDENTIFIER
        ::= { whispPlvModemObjects 4 }

modemAdmConfIpConfig OBJECT-TYPE
        SYNTAX  INTEGER {
                        dynamic(1),
                        static(2) }
        MAX-ACCESS read-write
        STATUS current
        DESCRIPTION
                "This object is used to enable or disable the DHCP client, to configure LAN IP Address
                 of the Modem. If the NAT functionality is enabled in the Modem, user will not be able to
                 enable DHCP client to configure the IP address and this object should behave as a
                 read-only object."
        DEFVAL { static }
        ::= { whispPlvModemAdmConfig 1 }

modemAdmConfIp OBJECT-TYPE
        SYNTAX  IpAddress
        MAX-ACCESS read-write
        STATUS current
        DESCRIPTION
                "This object is used to configure IP Address of the Modem. If the NAT functionality
                 is enabled in the Modem, then this object represents the LAN IP Address."
        ::= { whispPlvModemAdmConfig 2 }

modemAdmConfIpSubnetMask OBJECT-TYPE
        SYNTAX  IpAddress
        MAX-ACCESS read-write
        STATUS current
        DESCRIPTION
                "This object is used to configure IP Subnet Mask of the Modem. If the NAT functionality
                 is enabled in the Modem, then this object represents the LAN IP Subnet Mask."
        ::= { whispPlvModemAdmConfig 3 }

modemAdmConfNEK OBJECT-TYPE
        SYNTAX  DisplayString (SIZE (4..24))
        MAX-ACCESS read-write
        STATUS current
        DESCRIPTION
                "This object is used to configure Network Encryption Key of the Modem."
        ::= { whispPlvModemAdmConfig 4 }

modemAdmConfSnmpGetCommStr OBJECT-TYPE
        SYNTAX  DisplayString (SIZE (0..255))
        MAX-ACCESS read-write
        STATUS current
        DESCRIPTION
                "This object is used to configure SNMP 'Read' community string of the Modem."
        ::= { whispPlvModemAdmConfig 5 }

modemAdmConfSnmpSetCommStr OBJECT-TYPE
        SYNTAX  DisplayString (SIZE (0..255))
        MAX-ACCESS read-write
        STATUS current
        DESCRIPTION
                "This object is used to configure SNMP 'Read-Write' community string of the Modem."
        ::= { whispPlvModemAdmConfig 6 }

modemAdmConfSnmpAdminCommStr OBJECT-TYPE
        SYNTAX  DisplayString (SIZE (0..255))
        MAX-ACCESS read-write
        STATUS current
        DESCRIPTION
                "This object is used to configure SNMP 'Admin' community string of the Modem."
        ::= { whispPlvModemAdmConfig 7 }

modemAdmConfLoginUsername OBJECT-TYPE
        SYNTAX  DisplayString (SIZE (3..16))
        MAX-ACCESS read-write
        STATUS current
        DESCRIPTION
                "This object is used to configure Modem's System Management Login Username."
        ::= { whispPlvModemAdmConfig 8 }

modemAdmConfLoginPassword OBJECT-TYPE
        SYNTAX  DisplayString (SIZE (0..16))
        MAX-ACCESS read-write
        STATUS current
        DESCRIPTION
                "This object is used to configure Modem's System Management Login Password."
        ::= { whispPlvModemAdmConfig 9 }

modemAdmConfFtpServerIp OBJECT-TYPE
	SYNTAX  IpAddress
	MAX-ACCESS  read-write
	STATUS  current
	DESCRIPTION
		"This object is used to configure IP Address of FTP server hosting auto-upgrade files."
	::= {whispPlvModemAdmConfig 10 }

modemAdmConfFtpUsername OBJECT-TYPE
	SYNTAX  DisplayString (SIZE(0..16))
	MAX-ACCESS  read-write
	STATUS  current
	DESCRIPTION
		"This object is used to configure Username to login to a FTP server,
                for use with FTP-based auto-upgrade."
	::= {whispPlvModemAdmConfig 11 }

modemAdmConfFtpPassword OBJECT-TYPE
	SYNTAX  DisplayString (SIZE(0..16))
	MAX-ACCESS  read-write
	STATUS  current
	DESCRIPTION
		"This object is used to configure Password to login to a FTP server,
                for use with FTP-based auto-upgrade."
	::= {whispPlvModemAdmConfig 12 }

modemAdmConfFtpFile OBJECT-TYPE
	SYNTAX  DisplayString (SIZE(0..255))
	MAX-ACCESS  read-write
	STATUS  current
	DESCRIPTION
		"This object is used to configure Path and/or Filename of the firmware file,
                for use with FTP-based auto-upgrade."
	::= {whispPlvModemAdmConfig 13 }

modemAdmConfDeviceUpgradeStart OBJECT-TYPE
        SYNTAX  INTEGER {
                        upgrade(1),
                        disabled(2) }
        MAX-ACCESS read-write
        STATUS current
        DESCRIPTION
                "This object is used to start Firmware Upgrade process in the Modem.
                To start the upgrade process, this object should be set to '1'."
        DEFVAL { disabled }
        ::= { whispPlvModemAdmConfig 14 }

modemAdmConfSimUpgradeStart OBJECT-TYPE
        SYNTAX  INTEGER {
                        upgrade(1),
                        disabled(2) }
        MAX-ACCESS read-write
        STATUS current
        DESCRIPTION
                "This object is used to start Intellon Simple Module Firmware Upgrade process.
                To start the upgrade process, this object should be set to '1'."
        DEFVAL { disabled }
        ::= { whispPlvModemAdmConfig 15 }

modemAdmConfSystemReboot OBJECT-TYPE
        SYNTAX  INTEGER {
                        reboot(1),
                        disabled(2) }
        MAX-ACCESS read-write
        STATUS current
        DESCRIPTION
                "This object is used to Reboot the Modem.
                To reboot the modem, this object should be set to '1'."
        DEFVAL { disabled }
        ::= { whispPlvModemAdmConfig 16 }

modemAdmConfReset OBJECT-TYPE
        SYNTAX  INTEGER {
                        reset(1),
                        disabled(2) }
        MAX-ACCESS read-write
        STATUS current
        DESCRIPTION
                "This object is used to reset the Modem configuration to Factory Defaults.
                To reset the modem configuration to factory defaults, this object should
                be set to '1'."
        DEFVAL { disabled }
        ::= { whispPlvModemAdmConfig 17 }

-- Modem Admin WAN Configuration
--

whispPlvModemAdmWConfig OBJECT IDENTIFIER
        ::= { whispPlvModemObjects 5 }

modemAdmWConfNatConfig OBJECT-TYPE
        SYNTAX  INTEGER {
                        enabled(1),
                        disabled(2) }
        MAX-ACCESS read-write
        STATUS current
        DESCRIPTION
                "This object is used to Enable or Disable the NAT Functionality in the Modem."
        DEFVAL { disabled }
        ::= { whispPlvModemAdmWConfig 1 }

modemAdmWConfWanConfig OBJECT-TYPE
        SYNTAX  INTEGER {
                        dynamic(1),
                        static(2) }
        MAX-ACCESS read-write
        STATUS current
        DESCRIPTION
                "This object is used to Enable or Disable DHCP client, to configure the WAN IP Address.
                This object is accessible only when NAT functionality is enabled in the Modem."
        DEFVAL { static }
        ::= { whispPlvModemAdmWConfig 2 }

modemAdmWConfWanIp OBJECT-TYPE
        SYNTAX  IpAddress
        MAX-ACCESS read-write
        STATUS current
        DESCRIPTION
                "This object is used to configure WAN IP Address of the Modem. This object is
                accessible only when NAT functionality is enabled in the Modem."
        ::= { whispPlvModemAdmWConfig 3 }

modemAdmWConfSubnetMask OBJECT-TYPE
        SYNTAX  IpAddress
        MAX-ACCESS read-write
        STATUS current
        DESCRIPTION
                "This object is used to configure WAN IP Subnet Mask of the Modem. This object
                is accessible only when NAT functionality is enabled in the Modem."
        ::= { whispPlvModemAdmWConfig 4 }

modemAdmWConfGateway OBJECT-TYPE
        SYNTAX  IpAddress
        MAX-ACCESS read-write
        STATUS current
        DESCRIPTION
                "This object is used to configure Default Gateway IP of the Modem. This object
                is accessible only when NAT functionality is enabled in the Modem."
        ::= { whispPlvModemAdmWConfig 5 }

modemAdmWConfDNS1 OBJECT-TYPE
        SYNTAX  IpAddress
        MAX-ACCESS read-write
        STATUS current
        DESCRIPTION
                "This object is used to configure DNS Server #1. This object is accessible only
                when NAT functionality is enabled in the Modem."
        ::= { whispPlvModemAdmWConfig 6 }

modemAdmWConfDNS2 OBJECT-TYPE
        SYNTAX  IpAddress
        MAX-ACCESS read-write
        STATUS current
        DESCRIPTION
                "This object is used to configure DNS Server #2. This object is accessible only
                when NAT functionality is enabled in the Modem."
        ::= { whispPlvModemAdmWConfig 7 }

modemAdmWConfDhcpConfig OBJECT-TYPE
        SYNTAX  INTEGER {
                        enabled(1),
                        disabled(2) }
        MAX-ACCESS read-write
        STATUS current
        DESCRIPTION
                "This object is used to Enable or Disable DHCP Server. This object is accessible
                only when NAT functionality is enabled in the Modem."
        DEFVAL { disabled }
        ::= { whispPlvModemAdmWConfig 8 }

modemAdmWConfDhcpStartIp OBJECT-TYPE
        SYNTAX  IpAddress
        MAX-ACCESS read-write
        STATUS current
        DESCRIPTION
                "This object is used to configure Starting Address of the IP address block,
                that the DHCP Server can assign to its clients. This object is accessible
                only when NAT functionality is enabled in the Modem."
        ::= { whispPlvModemAdmWConfig 9 }

modemAdmWConfDhcpEndIp OBJECT-TYPE
        SYNTAX  IpAddress
        MAX-ACCESS read-write
        STATUS current
        DESCRIPTION
                "This object is used to configure Last Address of the IP address block, that
                the DHCP Server can assign to its clients. This object is accessible only when
                NAT functionality is enabled in the Modem."
        ::= { whispPlvModemAdmWConfig 10 }

modemAdmWConfDhcpLeaseTime OBJECT-TYPE
        SYNTAX  INTEGER {
                        thirtyMins(1),
                        oneHour(2),
                        twoHours(3),
                        twelveHours(4),
                        oneDay(5),
                        twoDays(6),
                        oneWeek(7),
                        twoWeeks(8)}
        MAX-ACCESS read-write
        STATUS current
        DESCRIPTION
                "This object is used to configure time period for which the IP address assigned
                to a client is valid. This object is accessible only when NAT functionality is
                enabled in the Modem."
        DEFVAL { oneDay }
        ::= { whispPlvModemAdmWConfig 11 }

modemAdmWConfDmzConfig OBJECT-TYPE
        SYNTAX  INTEGER {
                        enabled(1),
                        disabled(2) }
        MAX-ACCESS read-write
        STATUS current
        DESCRIPTION
                "This object is used to Enable or Disable the DMZ in the MOdem. This object is
                accessible only when NAT functionality is enabled in the Modem."
        DEFVAL { disabled }
        ::= { whispPlvModemAdmWConfig 12 }

modemAdmWConfDmzIp OBJECT-TYPE
        SYNTAX  IpAddress
        MAX-ACCESS read-write
        STATUS current
        DESCRIPTION
                "This object is used to configure DMZ IP Address of the Modem. This object is
                accessible only when NAT functionality is enabled in the Modem."
        ::= { whispPlvModemAdmWConfig 13 }

-- Modem Admin SNMP Access Configuration
--

whispPlvModemAdmSnmpAcessConfig OBJECT IDENTIFIER
        ::= { whispPlvModemObjects 6 }

modemAdmSnmpAccessIpNetwork1 OBJECT-TYPE
        SYNTAX  IpAddress
        MAX-ACCESS read-write
        STATUS current
        DESCRIPTION
                "This object is used to configure SNMP Access Network Address #1."
        ::= { whispPlvModemAdmSnmpAcessConfig 1 }

modemAdmSnmpAccessIpNetworkMask1 OBJECT-TYPE
        SYNTAX  IpAddress
        MAX-ACCESS read-write
        STATUS current
        DESCRIPTION
                "This object is used to configure SNMP Access Network Address Mask #1."
        ::= { whispPlvModemAdmSnmpAcessConfig 2 }

modemAdmSnmpAccessIpNetwork2 OBJECT-TYPE
        SYNTAX  IpAddress
        MAX-ACCESS read-write
        STATUS current
        DESCRIPTION
                "This object is used to configure SNMP Access Network Address #2."
        ::= { whispPlvModemAdmSnmpAcessConfig 3 }

modemAdmSnmpAccessIpNetworkMask2 OBJECT-TYPE
        SYNTAX  IpAddress
        MAX-ACCESS read-write
        STATUS current
        DESCRIPTION
                "This object is used to configure SNMP Access Network Address Mask #2."
        ::= { whispPlvModemAdmSnmpAcessConfig 4 }

modemAdmSnmpAccessIpNetwork3 OBJECT-TYPE
        SYNTAX  IpAddress
        MAX-ACCESS read-write
        STATUS current
        DESCRIPTION
                "This object is used to configure SNMP Access Network Address #3."
        ::= { whispPlvModemAdmSnmpAcessConfig 5 }

modemAdmSnmpAccessIpNetworkMask3 OBJECT-TYPE
        SYNTAX  IpAddress
        MAX-ACCESS read-write
        STATUS current
        DESCRIPTION
                "This object is used to configure SNMP Access Network Address Mask #3."
        ::= { whispPlvModemAdmSnmpAcessConfig 6 }

modemAdmSnmpAccessIpNetwork4 OBJECT-TYPE
        SYNTAX  IpAddress
        MAX-ACCESS read-write
        STATUS current
        DESCRIPTION
                "This object is used to configure SNMP Access Network Address #4."
        ::= { whispPlvModemAdmSnmpAcessConfig 7 }

modemAdmSnmpAccessIpNetworkMask4 OBJECT-TYPE
        SYNTAX  IpAddress
        MAX-ACCESS read-write
        STATUS current
        DESCRIPTION
                "This object is used to configure SNMP Access Network Address Mask #4."
        ::= { whispPlvModemAdmSnmpAcessConfig 8 }

modemAdmSnmpAccessIpNetwork5 OBJECT-TYPE
        SYNTAX  IpAddress
        MAX-ACCESS read-write
        STATUS current
        DESCRIPTION
                "This object is used to configure SNMP Access Network Address #5."
        ::= { whispPlvModemAdmSnmpAcessConfig 9 }

modemAdmSnmpAccessIpNetworkMask5 OBJECT-TYPE
        SYNTAX  IpAddress
        MAX-ACCESS read-write
        STATUS current
        DESCRIPTION
                "This object is used to configure SNMP Access Network Address Mask #5."
        ::= { whispPlvModemAdmSnmpAcessConfig 10 }

modemAdmSnmpAccessIpNetwork6 OBJECT-TYPE
        SYNTAX  IpAddress
        MAX-ACCESS read-write
        STATUS current
        DESCRIPTION
                "This object is used to configure SNMP Access Network Address #6."
        ::= { whispPlvModemAdmSnmpAcessConfig 11 }

modemAdmSnmpAccessIpNetworkMask6 OBJECT-TYPE
        SYNTAX  IpAddress
        MAX-ACCESS read-write
        STATUS current
        DESCRIPTION
                "This object is used to configure SNMP Access Network Address Mask #6."
        ::= { whispPlvModemAdmSnmpAcessConfig 12 }

modemAdmSnmpAccessIpNetwork7 OBJECT-TYPE
        SYNTAX  IpAddress
        MAX-ACCESS read-write
        STATUS current
        DESCRIPTION
                "This object is used to configure SNMP Access Network Address #7."
        ::= { whispPlvModemAdmSnmpAcessConfig 13 }

modemAdmSnmpAccessIpNetworkMask7 OBJECT-TYPE
        SYNTAX  IpAddress
        MAX-ACCESS read-write
        STATUS current
        DESCRIPTION
                "This object is used to configure SNMP Access Network Address Mask #7."
        ::= { whispPlvModemAdmSnmpAcessConfig 14 }

modemAdmSnmpAccessIpNetwork8 OBJECT-TYPE
        SYNTAX  IpAddress
        MAX-ACCESS read-write
        STATUS current
        DESCRIPTION
                "This object is used to configure SNMP Access Network Address #8."
        ::= { whispPlvModemAdmSnmpAcessConfig 15 }

modemAdmSnmpAccessIpNetworkMask8 OBJECT-TYPE
        SYNTAX  IpAddress
        MAX-ACCESS read-write
        STATUS current
        DESCRIPTION
                "This object is used to configure SNMP Access Network Address Mask #8."
        ::= { whispPlvModemAdmSnmpAcessConfig 16 }

modemAdmSnmpAccessIpNetwork9 OBJECT-TYPE
        SYNTAX  IpAddress
        MAX-ACCESS read-write
        STATUS current
        DESCRIPTION
                "This object is used to configure SNMP Access Network Address #9."
        ::= { whispPlvModemAdmSnmpAcessConfig 17 }

modemAdmSnmpAccessIpNetworkMask9 OBJECT-TYPE
        SYNTAX  IpAddress
        MAX-ACCESS read-write
        STATUS current
        DESCRIPTION
                "This object is used to configure SNMP Access Network Address Mask #9."
        ::= { whispPlvModemAdmSnmpAcessConfig 18 }

modemAdmSnmpAccessIpNetwork10 OBJECT-TYPE
        SYNTAX  IpAddress
        MAX-ACCESS read-write
        STATUS current
        DESCRIPTION
                "This object is used to configure SNMP Access Network Address #10."
        ::= { whispPlvModemAdmSnmpAcessConfig 19 }

modemAdmSnmpAccessIpNetworkMask10 OBJECT-TYPE
        SYNTAX  IpAddress
        MAX-ACCESS read-write
        STATUS current
        DESCRIPTION
                "This object is used to configure SNMP Access Network Address Mask #10."
        ::= { whispPlvModemAdmSnmpAcessConfig 20 }


-- Modem Admin Repeater Configuration
--

whispPlvModemAdmRepeaterConfig OBJECT IDENTIFIER
        ::= { whispPlvModemObjects 7 }

modemAdmRepeaterConfOperatingMode OBJECT-TYPE
        SYNTAX  INTEGER {
                        normal(1),
                        repeater(2),
                        useWithRepeater(3) }
        MAX-ACCESS read-write
        STATUS current
        DESCRIPTION
                "This object is used to configure the Modem operating mode.
                Modem should be rebooted for the change in the configuration to take effect."
        DEFVAL { normal }
        ::= { whispPlvModemAdmRepeaterConfig 1 }

modemAdmRepeaterConfModemMAC1 OBJECT-TYPE
        SYNTAX  MacAddress
        MAX-ACCESS read-write
        STATUS current
        DESCRIPTION
                "This object represents the MAC Address of Modem 1, that uses the Repeater."
        ::= { whispPlvModemAdmRepeaterConfig 2 }

modemAdmRepeaterConfModemMAC2 OBJECT-TYPE
        SYNTAX  MacAddress
        MAX-ACCESS read-write
        STATUS current
        DESCRIPTION
                "This object represents the MAC Address of Modem 2, that uses the Repeater."
        ::= { whispPlvModemAdmRepeaterConfig 3 }

modemAdmRepeaterConfModemMAC3 OBJECT-TYPE
        SYNTAX  MacAddress
        MAX-ACCESS read-write
        STATUS current
        DESCRIPTION
                "This object represents the MAC Address of Modem 3, that uses the Repeater."
        ::= { whispPlvModemAdmRepeaterConfig 4 }

modemAdmRepeaterConfModemMAC4 OBJECT-TYPE
        SYNTAX  MacAddress
        MAX-ACCESS read-write
        STATUS current
        DESCRIPTION
                "This object represents the MAC Address of Modem 4, that uses the Repeater."
        ::= { whispPlvModemAdmRepeaterConfig 5 }


-- Modem Admin VLAN Configuration
--

whispPlvModemAdmVLANTable OBJECT-TYPE
        SYNTAX  SEQUENCE OF WhispPlvModemAdmVLANEntry
        MAX-ACCESS not-accessible
        STATUS current
        DESCRIPTION
                "This table contains one row per device connected behind the Modem, either
                directly OR using a switch"
        ::= { whispPlvModemObjects 8 }

whispPlvModemAdmVLANEntry OBJECT-TYPE
        SYNTAX  WhispPlvModemAdmVLANEntry
        MAX-ACCESS not-accessible
        STATUS current
        DESCRIPTION
                "VLAN information of the device connected behind the Modem."
        INDEX { modemAdmVLANIndex }
        ::= { whispPlvModemAdmVLANTable 1 }

WhispPlvModemAdmVLANEntry ::= SEQUENCE {
        modemAdmVLANIndex               INTEGER,
        modemAdmVLANPhysAddress         MacAddress,
        modemAdmVLANId                  Integer32 }

modemAdmVLANIndex OBJECT-TYPE
        SYNTAX  Integer32 (1..2147483647)
        MAX-ACCESS not-accessible
        STATUS current
        DESCRIPTION
                "The value of this object identifies the index to this entry."
        ::= { whispPlvModemAdmVLANEntry 1 }

modemAdmVLANPhysAddress OBJECT-TYPE
        SYNTAX  MacAddress
        MAX-ACCESS read-only
        STATUS current
        DESCRIPTION
                "This object indicates the MAC Address of the device connected behind the Modem."
        ::= { whispPlvModemAdmVLANEntry 2 }

modemAdmVLANId OBJECT-TYPE
        SYNTAX  Integer32 (1..4095)
        MAX-ACCESS read-write
        STATUS current
        DESCRIPTION
                "This object indicates the VLAN ID of the device connected behind the Modem."
        ::= { whispPlvModemAdmVLANEntry 3 }


-- Notification Types
--

whispPlvModemEvents OBJECT IDENTIFIER
        ::= { whispPlvModemMIB 2 }

modemTrapPrefix OBJECT IDENTIFIER
        ::= { whispPlvModemEvents 0 }

modemTrapDeviceUpgradeStarted NOTIFICATION-TYPE
        OBJECTS {
                modemInfoDeviceUpgradeStatus,
                modemInfoDeviceFirmwareVer }
        STATUS current
        DESCRIPTION
                "This Notification is generated if the Modem has started the firmware Upgrade process."
        ::= { modemTrapPrefix 1 }

modemTrapDeviceUpgradeCompleted NOTIFICATION-TYPE
        OBJECTS {
                modemInfoDeviceUpgradeStatus,
                modemInfoDeviceFirmwareVer }
        STATUS current
        DESCRIPTION
                "This Notification is generated once the Upgrade process is completed."
        ::= { modemTrapPrefix 2 }

modemTrapSimUpgradeStarted NOTIFICATION-TYPE
        OBJECTS {
                modemInfoSimUpgradeStatus,
                modemInfoSimFirmwareVer }
        STATUS current
        DESCRIPTION
                "This Notification is generated if the Intellon Simple Module Upgrade process
                is started."
        ::= { modemTrapPrefix 3 }

modemTrapSimUpgradeCompleted NOTIFICATION-TYPE
        OBJECTS {
                modemInfoSimUpgradeStatus,
                modemInfoSimFirmwareVer }
        STATUS current
        DESCRIPTION
                "This Notification is generated once the Simple Module Upgrade process is completed."
        ::= { modemTrapPrefix 4 }

-- Conformance
--

whispPlvModemConformance OBJECT IDENTIFIER
        ::= { whispPlvModemMIB 3 }

-- Groups
--

whispPlvModemGroups OBJECT IDENTIFIER
        ::= { whispPlvModemConformance 1 }

whispPlvModemCompliances OBJECT IDENTIFIER
        ::= { whispPlvModemConformance 2 }

whispPlvModemInfoGroup OBJECT-GROUP
        OBJECTS {
                modemInfoModel,
                modemInfoSerialNumber,
                modemInfoDeviceMac,
                modemInfoPlcMac,
                modemInfoHardwareVer,
                modemInfoDeviceFirmwareVer,
                modemInfoBootLoaderVer,
                modemInfoSimFirmwareVer,
                modemInfoDeviceUpgradeStatus,
                modemInfoSimUpgradeStatus,
                modemInfoCurrentMode,
                modemInfoActiveBandwidthConfig,
                modemInfoActiveUpLinkBandwidth,
                modemInfoActiveDownLinkBandwidth }
        STATUS current
        DESCRIPTION
                "The collection of objects that gives Modem device information."
        ::= { whispPlvModemGroups 1 }

whispPlvModemConfigGroup OBJECT-GROUP
        OBJECTS {
                modemConfPacketPriorityConfig,
                modemConfFixedQoSConfig,
                modemConfUpLinkDataRate,
                modemConfDownLinkDataRate,
                modemConfPSD,
                modemConfUpLinkMir,
                modemConfDownLinkMir }
        STATUS current
        DESCRIPTION
                "The collection of objects used to configure the Modem.
                These objects are accessible to everyone."
        ::= { whispPlvModemGroups 2 }

whispPlvModemTrapConfigGroup OBJECT-GROUP
        OBJECTS {
                modemConfTrapIp1,
                modemConfTrapCommStr1,
                modemConfTrapIp2,
                modemConfTrapCommStr2,
                modemConfTrapIp3,
                modemConfTrapCommStr3,
                modemConfTrapIp4,
                modemConfTrapCommStr4,
                modemConfTrapIp5,
                modemConfTrapCommStr5,
                modemConfTrapIp6,
                modemConfTrapCommStr6,
                modemConfTrapIp7,
                modemConfTrapCommStr7,
                modemConfTrapIp8,
                modemConfTrapCommStr8,
                modemConfTrapIp9,
                modemConfTrapCommStr9,
                modemConfTrapIp10,
                modemConfTrapCommStr10 }
        STATUS current
        DESCRIPTION
                "The collection of Modems SNMP Trap Configuration objects.
                These objects are accessible to everyone."
        ::= { whispPlvModemGroups 3 }

whispPlvModemAdmConfigGroup OBJECT-GROUP
        OBJECTS {
                modemAdmConfIpConfig,
                modemAdmConfIp,
                modemAdmConfIpSubnetMask,
                modemAdmConfNEK,
                modemAdmConfSnmpGetCommStr,
                modemAdmConfSnmpSetCommStr,
                modemAdmConfSnmpAdminCommStr,
                modemAdmConfLoginUsername,
                modemAdmConfLoginPassword,
                modemAdmConfFtpServerIp,
                modemAdmConfFtpUsername,
                modemAdmConfFtpPassword,
                modemAdmConfFtpFile,
                modemAdmConfDeviceUpgradeStart,
                modemAdmConfSimUpgradeStart,
                modemAdmConfSystemReboot,
                modemAdmConfReset }
        STATUS current
        DESCRIPTION
                "The collection of objects that are used to configure the Modem.
                These objects are accessible only thru 'admin' community string."
        ::= { whispPlvModemGroups 4 }

whispPlvModemAdmWConfigGroup OBJECT-GROUP
        OBJECTS {
                modemAdmWConfNatConfig,
                modemAdmWConfWanConfig,
                modemAdmWConfWanIp,
                modemAdmWConfSubnetMask,
                modemAdmWConfGateway,
                modemAdmWConfDNS1,
                modemAdmWConfDNS2,
                modemAdmWConfDhcpConfig,
                modemAdmWConfDhcpStartIp,
                modemAdmWConfDhcpEndIp,
                modemAdmWConfDhcpLeaseTime,
                modemAdmWConfDmzConfig,
                modemAdmWConfDmzIp }
        STATUS current
        DESCRIPTION
                "The collection of Modems WAN Configuration objects. These objects
                are accessible only thru 'admin' community string."
        ::= { whispPlvModemGroups 5 }

whispPlvModemAdmSnmpAcessConfigGroup OBJECT-GROUP
        OBJECTS {
                modemAdmSnmpAccessIpNetwork1,
                modemAdmSnmpAccessIpNetworkMask1,
                modemAdmSnmpAccessIpNetwork2,
                modemAdmSnmpAccessIpNetworkMask2,
                modemAdmSnmpAccessIpNetwork3,
                modemAdmSnmpAccessIpNetworkMask3,
                modemAdmSnmpAccessIpNetwork4,
                modemAdmSnmpAccessIpNetworkMask4,
                modemAdmSnmpAccessIpNetwork5,
                modemAdmSnmpAccessIpNetworkMask5,
                modemAdmSnmpAccessIpNetwork6,
                modemAdmSnmpAccessIpNetworkMask6,
                modemAdmSnmpAccessIpNetwork7,
                modemAdmSnmpAccessIpNetworkMask7,
                modemAdmSnmpAccessIpNetwork8,
                modemAdmSnmpAccessIpNetworkMask8,
                modemAdmSnmpAccessIpNetwork9,
                modemAdmSnmpAccessIpNetworkMask9,
                modemAdmSnmpAccessIpNetwork10,
                modemAdmSnmpAccessIpNetworkMask10 }
        STATUS current
        DESCRIPTION
                "The collection of Modems SNMP Access Network objects. These objects
                are accessible only thru 'admin' community string."
        ::= { whispPlvModemGroups 6 }

whispPlvModemNotificationsGroup NOTIFICATION-GROUP
        NOTIFICATIONS {
                modemTrapDeviceUpgradeStarted,
                modemTrapDeviceUpgradeCompleted,
                modemTrapSimUpgradeStarted,
                modemTrapSimUpgradeCompleted }
        STATUS current
        DESCRIPTION
                "The collection of Notifications generated by the Modem."
        ::= { whispPlvModemGroups 7 }

whispPlvModemAdmRepeaterConfigGroup OBJECT-GROUP
        OBJECTS {
                modemAdmRepeaterConfOperatingMode,
                modemAdmRepeaterConfModemMAC1,
                modemAdmRepeaterConfModemMAC2,
                modemAdmRepeaterConfModemMAC3,
                modemAdmRepeaterConfModemMAC4 }
        STATUS current
        DESCRIPTION
                "The collection of Repeater Configuration Objects. These objects
                are accessible only thru 'admin' community string."
        ::= { whispPlvModemGroups 8 }

whispPlvModemAdmVLANConfigGroup OBJECT-GROUP
        OBJECTS {
                modemAdmVLANPhysAddress,
                modemAdmVLANId }
        STATUS current
        DESCRIPTION
                "The collection of VLAN Configuration Objects. These objects are accessible
                only thru 'admin' community string."
        ::= { whispPlvModemGroups 9 }

-- Compliance
--

whispPlvModemCompliance MODULE-COMPLIANCE
        STATUS current
        DESCRIPTION
                "The compliance statement of SNMP entities which implement the WHISP-PLV-MODEM-MIB."
        MODULE  -- This Module
        MANDATORY-GROUPS {
                         whispPlvModemInfoGroup,
                         whispPlvModemConfigGroup,
                         whispPlvModemTrapConfigGroup,
                         whispPlvModemAdmConfigGroup,
                         whispPlvModemAdmWConfigGroup,
                         whispPlvModemAdmSnmpAcessConfigGroup,
                         whispPlvModemNotificationsGroup,
                         whispPlvModemAdmRepeaterConfigGroup,
                         whispPlvModemAdmVLANConfigGroup }

       ::= { whispPlvModemCompliances 1 }

END
