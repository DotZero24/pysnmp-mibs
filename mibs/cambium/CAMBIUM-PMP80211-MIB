--Cambium MIB Release 4.7.1

CAMBIUM-PMP80211-MIB DEFINITIONS ::= BEGIN

IMPORTS
		OBJECT-TYPE, MODULE-IDENTITY, NOTIFICATION-TYPE, enterprises,
		IpAddress, Integer32, Counter32, Counter64, TimeTicks
				FROM SNMPv2-SMI
		OBJECT-GROUP
				FROM SNMPv2-CONF
		MacAddress, DisplayString
				FROM SNMPv2-TC
		Ipv6Address
				FROM IPV6-TC;

pmpMibTree MODULE-IDENTITY
	LAST-UPDATED "202002131900Z"
	ORGANIZATION
		"Cambium Networks Inc."
	CONTACT-INFO
		"Cambium Networks Support"
	DESCRIPTION
		"This module contains MIB definitions for APs."

	REVISION "202002131900Z"
	DESCRIPTION
		"Current Production Version."

::= { cambium 21 }

cambium									OBJECT IDENTIFIER ::= { enterprises 17713 }

cambiumpmp80211SystemTraps				OBJECT IDENTIFIER ::= { pmpMibTree 0 }
cambiumPmp80211SystemStatus				OBJECT IDENTIFIER ::= { pmpMibTree 1 }
cambiumPmp80211SystemMonitoring			OBJECT IDENTIFIER ::= { pmpMibTree 2 }
cambiumpmp80211SystemConfiguration		OBJECT IDENTIFIER ::= { pmpMibTree 3 }
cambiumpmp80211SystemActions			OBJECT IDENTIFIER ::= { pmpMibTree 4 }
cambiumpmp80211Tools					OBJECT IDENTIFIER ::= { pmpMibTree 6 }
cambiumHWGroupInfo						OBJECT IDENTIFIER ::= { pmpMibTree 9 }
ePMPavenger5gconnectorizedsync 			OBJECT IDENTIFIER ::= { cambiumHWGroupInfo 0 }
ePMPavenger5gconnectorized 			OBJECT IDENTIFIER ::= { cambiumHWGroupInfo 1 }
ePMPavenger5gintegrated 			OBJECT IDENTIFIER ::= { cambiumHWGroupInfo 2 }
ePMPavenger2gconnectorizedsync 			OBJECT IDENTIFIER ::= { cambiumHWGroupInfo 3 }
ePMPavenger2gconnectorized 			OBJECT IDENTIFIER ::= { cambiumHWGroupInfo 4 }
ePMPavenger2gintegrated 			OBJECT IDENTIFIER ::= { cambiumHWGroupInfo 5 }
ePMPironman25grow 			OBJECT IDENTIFIER ::= { cambiumHWGroupInfo 6 }
ePMPironman22grow 			OBJECT IDENTIFIER ::= { cambiumHWGroupInfo 7 }
ePMPironman25gfccextflt 			OBJECT IDENTIFIER ::= { cambiumHWGroupInfo 8 }
ePMPironman22gfccrowextflt 			OBJECT IDENTIFIER ::= { cambiumHWGroupInfo 9 }
ePMPhawkeye 			OBJECT IDENTIFIER ::= { cambiumHWGroupInfo 10 }
ePMPironlad5grow 			OBJECT IDENTIFIER ::= { cambiumHWGroupInfo 11 }
ePMPironlad5gfccextflt 			OBJECT IDENTIFIER ::= { cambiumHWGroupInfo 12 }
ePMPdarkchocolate5grow 			OBJECT IDENTIFIER ::= { cambiumHWGroupInfo 13 }
ePMPdarkchocolate5gfcc 			OBJECT IDENTIFIER ::= { cambiumHWGroupInfo 14 }
ePMPhawkeyecrystal 			OBJECT IDENTIFIER ::= { cambiumHWGroupInfo 15 }
ePMPmargaret6gironlad 			OBJECT IDENTIFIER ::= { cambiumHWGroupInfo 16 }
ePMPmargaret6gconnectorizedsync 			OBJECT IDENTIFIER ::= { cambiumHWGroupInfo 17 }
ePMPmargaret6gconnectorized 			OBJECT IDENTIFIER ::= { cambiumHWGroupInfo 18 }
ePMPelectra25gconnectorizedsync 			OBJECT IDENTIFIER ::= { cambiumHWGroupInfo 19 }
ePMPelectra25gconnectorized 			OBJECT IDENTIFIER ::= { cambiumHWGroupInfo 20 }
ePMPforce1305g 			OBJECT IDENTIFIER ::= { cambiumHWGroupInfo 22 }
ePMPforce1302g 			OBJECT IDENTIFIER ::= { cambiumHWGroupInfo 23 }
ePMPforce200l 			OBJECT IDENTIFIER ::= { cambiumHWGroupInfo 24 }
ePMPforce200lv2 			OBJECT IDENTIFIER ::= { cambiumHWGroupInfo 25 }
ePMPptp5505gintegratedfcc 			OBJECT IDENTIFIER ::= { cambiumHWGroupInfo 33 }
ePMPptp5505gconnectorizedfcc 			OBJECT IDENTIFIER ::= { cambiumHWGroupInfo 34 }
ePMPf300fcc 			OBJECT IDENTIFIER ::= { cambiumHWGroupInfo 35 }
ePMPf300row 			OBJECT IDENTIFIER ::= { cambiumHWGroupInfo 36 }
ePMPepmp3000fcc 			OBJECT IDENTIFIER ::= { cambiumHWGroupInfo 37 }
ePMPf220fcc 			OBJECT IDENTIFIER ::= { cambiumHWGroupInfo 38 }
ePMPf220row 			OBJECT IDENTIFIER ::= { cambiumHWGroupInfo 39 }
ePMPepmp3000row 			OBJECT IDENTIFIER ::= { cambiumHWGroupInfo 40 }
ePMPptp5505gintegratedrow 			OBJECT IDENTIFIER ::= { cambiumHWGroupInfo 41 }
ePMPptp5505gconnectorizedrow 			OBJECT IDENTIFIER ::= { cambiumHWGroupInfo 42 }
ePMPmystiquefccsync 			OBJECT IDENTIFIER ::= { cambiumHWGroupInfo 43 }
ePMPmystiquerowsync 			OBJECT IDENTIFIER ::= { cambiumHWGroupInfo 44 }
ePMPmystiquefcc 			OBJECT IDENTIFIER ::= { cambiumHWGroupInfo 45 }
ePMPmystiquerow 			OBJECT IDENTIFIER ::= { cambiumHWGroupInfo 46 }
ePMPxorn13fcc 			OBJECT IDENTIFIER ::= { cambiumHWGroupInfo 47 }
ePMPxorn13row 			OBJECT IDENTIFIER ::= { cambiumHWGroupInfo 48 }
ePMPxorn19fcc 			OBJECT IDENTIFIER ::= { cambiumHWGroupInfo 49 }
ePMPxorn19row 			OBJECT IDENTIFIER ::= { cambiumHWGroupInfo 50 }
ePMPxorn19rip67row 			OBJECT IDENTIFIER ::= { cambiumHWGroupInfo 51 }
ePMPxorn19rip67fcc 			OBJECT IDENTIFIER ::= { cambiumHWGroupInfo 52 }
ePMPhellcowfcc 			OBJECT IDENTIFIER ::= { cambiumHWGroupInfo 53 }
ePMPhellcowrow 			OBJECT IDENTIFIER ::= { cambiumHWGroupInfo 54 }
ePMPf300fccv2 			OBJECT IDENTIFIER ::= { cambiumHWGroupInfo 55 }
ePMPf30025l 			OBJECT IDENTIFIER ::= { cambiumHWGroupInfo 58 }
ePMPf30025lv2 			OBJECT IDENTIFIER ::= { cambiumHWGroupInfo 60 }
ePMPf30013l 			OBJECT IDENTIFIER ::= { cambiumHWGroupInfo 61 }
ePMPe510 			OBJECT IDENTIFIER ::= { cambiumHWGroupInfo 62 }
ePMPepmp60004x46growfcc 			OBJECT IDENTIFIER ::= { cambiumHWGroupInfo 53264 }
ePMPepmp40008x85grow 			OBJECT IDENTIFIER ::= { cambiumHWGroupInfo 53280 }
ePMPepmp4500c8x85grow 			OBJECT IDENTIFIER ::= { cambiumHWGroupInfo 53281 }
ePMPepmp40008x85gfcc 			OBJECT IDENTIFIER ::= { cambiumHWGroupInfo 53288 }
ePMPepmp4500c8x85gfcc 			OBJECT IDENTIFIER ::= { cambiumHWGroupInfo 53289 }
ePMPepmp4600l6growfcc 			OBJECT IDENTIFIER ::= { cambiumHWGroupInfo 53296 }
ePMPf400gps5grow 			OBJECT IDENTIFIER ::= { cambiumHWGroupInfo 53344 }
ePMPf400gps5gfcc 			OBJECT IDENTIFIER ::= { cambiumHWGroupInfo 53352 }
ePMPcnppilottiger5g 			OBJECT IDENTIFIER ::= { cambiumHWGroupInfo 53376 }
ePMPf4255grow 			OBJECT IDENTIFIER ::= { cambiumHWGroupInfo 53504 }
ePMPf400c5grow 			OBJECT IDENTIFIER ::= { cambiumHWGroupInfo 53505 }
ePMPf4255gfcc 			OBJECT IDENTIFIER ::= { cambiumHWGroupInfo 53512 }
ePMPf400c5gfcc 			OBJECT IDENTIFIER ::= { cambiumHWGroupInfo 53513 }
ePMPf600c6growfcc 			OBJECT IDENTIFIER ::= { cambiumHWGroupInfo 53520 }
ePMPf600c6gfcc 			OBJECT IDENTIFIER ::= { cambiumHWGroupInfo 53528 }
ePMPf4165grow 			OBJECT IDENTIFIER ::= { cambiumHWGroupInfo 53536 }
ePMPf425l5grow 			OBJECT IDENTIFIER ::= { cambiumHWGroupInfo 53537 }
ePMPf425ulnomcu5grow 			OBJECT IDENTIFIER ::= { cambiumHWGroupInfo 53538 }
ePMPf4165gfcc 			OBJECT IDENTIFIER ::= { cambiumHWGroupInfo 53544 }
ePMPf425l5gfcc 			OBJECT IDENTIFIER ::= { cambiumHWGroupInfo 53545 }
ePMPf6166grow 			OBJECT IDENTIFIER ::= { cambiumHWGroupInfo 53552 }
ePMPf6256grow 			OBJECT IDENTIFIER ::= { cambiumHWGroupInfo 53553 }
ePMPf616usbgps6gfcc 			OBJECT IDENTIFIER ::= { cambiumHWGroupInfo 53560 }
ePMPf625usbgps6gfcc 			OBJECT IDENTIFIER ::= { cambiumHWGroupInfo 53561 }
ePMPnanostationm5v3xw 			OBJECT IDENTIFIER ::= { cambiumHWGroupInfo 100 }
ePMPnanostationlocom5v3 			OBJECT IDENTIFIER ::= { cambiumHWGroupInfo 110 }
ePMPnanostationlocom2xw 			OBJECT IDENTIFIER ::= { cambiumHWGroupInfo 111 }
ePMPnanostationlocom2v2xw 			OBJECT IDENTIFIER ::= { cambiumHWGroupInfo 112 }
ePMPnanostationlocom2v3xw 			OBJECT IDENTIFIER ::= { cambiumHWGroupInfo 113 }
ePMProcketm5xwv1 			OBJECT IDENTIFIER ::= { cambiumHWGroupInfo 120 }
ePMProcketm5x3wv2 			OBJECT IDENTIFIER ::= { cambiumHWGroupInfo 121 }
ePMPnanobeamm516xw 			OBJECT IDENTIFIER ::= { cambiumHWGroupInfo 130 }
ePMPnanobeamm519xw 			OBJECT IDENTIFIER ::= { cambiumHWGroupInfo 131 }
ePMPnanobeamm2xw 			OBJECT IDENTIFIER ::= { cambiumHWGroupInfo 132 }
ePMPrbsxtlite5 			OBJECT IDENTIFIER ::= { cambiumHWGroupInfo 140 }
ePMPintelbras 			OBJECT IDENTIFIER ::= { cambiumHWGroupInfo 141 }
ePMPlhg5 			OBJECT IDENTIFIER ::= { cambiumHWGroupInfo 142 }
ePMPdisclite5 			OBJECT IDENTIFIER ::= { cambiumHWGroupInfo 143 }
ePMPmk911l 			OBJECT IDENTIFIER ::= { cambiumHWGroupInfo 144 }
ePMPsextant 			OBJECT IDENTIFIER ::= { cambiumHWGroupInfo 145 }
ePMPpowerbeamm5300 			OBJECT IDENTIFIER ::= { cambiumHWGroupInfo 150 }
ePMPpowerbeamm5400 			OBJECT IDENTIFIER ::= { cambiumHWGroupInfo 151 }
ePMPpowerbeamm5620 			OBJECT IDENTIFIER ::= { cambiumHWGroupInfo 152 }
ePMPpowerbeamm2400 			OBJECT IDENTIFIER ::= { cambiumHWGroupInfo 153 }
ePMPpowerbeamm5400iso 			OBJECT IDENTIFIER ::= { cambiumHWGroupInfo 154 }
ePMPpowerbeamm5300iso 			OBJECT IDENTIFIER ::= { cambiumHWGroupInfo 155 }
ePMPpowerbeamm5600iso 			OBJECT IDENTIFIER ::= { cambiumHWGroupInfo 156 }
ePMPnanostationm5v1xm 			OBJECT IDENTIFIER ::= { cambiumHWGroupInfo 170 }
ePMPnanostationm5v2xm 			OBJECT IDENTIFIER ::= { cambiumHWGroupInfo 171 }
ePMPnanostationm365xm 			OBJECT IDENTIFIER ::= { cambiumHWGroupInfo 172 }
ePMPnanostationm2v1xm 			OBJECT IDENTIFIER ::= { cambiumHWGroupInfo 173 }
ePMPnanostationm3xm 			OBJECT IDENTIFIER ::= { cambiumHWGroupInfo 174 }
ePMPnanostationm900xm 			OBJECT IDENTIFIER ::= { cambiumHWGroupInfo 175 }
ePMPnanostationm2v2xm 			OBJECT IDENTIFIER ::= { cambiumHWGroupInfo 176 }
ePMPnanostationlocom5v1xm 			OBJECT IDENTIFIER ::= { cambiumHWGroupInfo 180 }
ePMPnanostationlocom5v2xm 			OBJECT IDENTIFIER ::= { cambiumHWGroupInfo 181 }
ePMPnanostationlocom900xm 			OBJECT IDENTIFIER ::= { cambiumHWGroupInfo 182 }
ePMPnanostationlocom2xm 			OBJECT IDENTIFIER ::= { cambiumHWGroupInfo 183 }
ePMPnanobridgem365xm 			OBJECT IDENTIFIER ::= { cambiumHWGroupInfo 190 }
ePMPnanobridgem900xm 			OBJECT IDENTIFIER ::= { cambiumHWGroupInfo 191 }
ePMPnanobridgem3xm 			OBJECT IDENTIFIER ::= { cambiumHWGroupInfo 192 }
ePMPnanobridgem5nb5g22xm 			OBJECT IDENTIFIER ::= { cambiumHWGroupInfo 193 }
ePMPnanobridgem5nb5g25xm 			OBJECT IDENTIFIER ::= { cambiumHWGroupInfo 194 }
ePMPnanobridgem5nbxm 			OBJECT IDENTIFIER ::= { cambiumHWGroupInfo 195 }
ePMPnanobridgem2v1xm 			OBJECT IDENTIFIER ::= { cambiumHWGroupInfo 196 }
ePMPnanobridgem2v2xm 			OBJECT IDENTIFIER ::= { cambiumHWGroupInfo 197 }
ePMPintelbraswom5amimo 			OBJECT IDENTIFIER ::= { cambiumHWGroupInfo 200 }
ePMPintelbraswom5a23 			OBJECT IDENTIFIER ::= { cambiumHWGroupInfo 201 }
ePMPpowerbridgem365xm 			OBJECT IDENTIFIER ::= { cambiumHWGroupInfo 210 }
ePMPpowerbridgem3xm 			OBJECT IDENTIFIER ::= { cambiumHWGroupInfo 211 }
ePMPnanostationm6xm 			OBJECT IDENTIFIER ::= { cambiumHWGroupInfo 220 }
ePMProcketm5v1xm 			OBJECT IDENTIFIER ::= { cambiumHWGroupInfo 241 }
ePMProcketm5v2xm 			OBJECT IDENTIFIER ::= { cambiumHWGroupInfo 242 }
ePMProcketm5v3xm 			OBJECT IDENTIFIER ::= { cambiumHWGroupInfo 243 }
ePMProcketm5v4xm 			OBJECT IDENTIFIER ::= { cambiumHWGroupInfo 244 }
ePMProcketm2v1xm 			OBJECT IDENTIFIER ::= { cambiumHWGroupInfo 245 }
ePMProcketm2v2xm 			OBJECT IDENTIFIER ::= { cambiumHWGroupInfo 246 }
ePMProcketm2v3xm 			OBJECT IDENTIFIER ::= { cambiumHWGroupInfo 247 }
ePMProcketm2v4xm 			OBJECT IDENTIFIER ::= { cambiumHWGroupInfo 248 }
cambiumGeneralStatus					OBJECT IDENTIFIER ::= { cambiumPmp80211SystemStatus 1 }
cambiumRFStatus							OBJECT IDENTIFIER ::= { cambiumPmp80211SystemStatus 2 }
cambiumGPSStatus						OBJECT IDENTIFIER ::= { cambiumPmp80211SystemStatus 3 }
cambiumLinkStatus						OBJECT IDENTIFIER ::= { cambiumPmp80211SystemStatus 4 }
cambiumAcsStatus						OBJECT IDENTIFIER ::= { cambiumPmp80211SystemStatus 5 }
cambiumMcastStatus						OBJECT IDENTIFIER ::= { cambiumPmp80211SystemStatus 6 }
cambiumDhcpStatus						OBJECT IDENTIFIER ::= { cambiumPmp80211SystemStatus 7 }
cambiumLicenseInfo						OBJECT IDENTIFIER ::= { cambiumPmp80211SystemStatus 8 }
cambiumRadiusVSAStatus					OBJECT IDENTIFIER ::= { cambiumPmp80211SystemStatus 9 }
cambiumCCTVStatus						OBJECT IDENTIFIER ::= { cambiumPmp80211SystemStatus 10 }
cambiumPerformanceMonitoring			OBJECT IDENTIFIER ::= { cambiumPmp80211SystemMonitoring 1 }
cambiumRealTimeStatsMonitoring			OBJECT IDENTIFIER ::= { cambiumPmp80211SystemMonitoring 2 }
cambiumAdvancedPerformanceMonitoring	OBJECT IDENTIFIER ::= { cambiumPmp80211SystemMonitoring 3 }
wlanMCSPackets							OBJECT IDENTIFIER ::= { cambiumPerformanceMonitoring 114 }
cambiumSystemLog						OBJECT IDENTIFIER ::= { cambiumpmp80211SystemConfiguration 1 }
cambiumDHCP								OBJECT IDENTIFIER ::= { cambiumpmp80211SystemConfiguration 2 }
cambiumSSHServer						OBJECT IDENTIFIER ::= { cambiumpmp80211SystemConfiguration 3 }
network									OBJECT IDENTIFIER ::= { cambiumpmp80211SystemConfiguration 4 }
networkLan								OBJECT IDENTIFIER ::= { network 2 }
lanSwitch								OBJECT IDENTIFIER ::= { networkLan 100 }
networkWan								OBJECT IDENTIFIER ::= { network 3 }
mgmtVLAN								OBJECT IDENTIFIER ::= { network 4 }
dataVLAN								OBJECT IDENTIFIER ::= { network 5 }
networkBridge							OBJECT IDENTIFIER ::= { network 7 }
mcastVLAN								OBJECT IDENTIFIER ::= { network 15 }
mgmtIF									OBJECT IDENTIFIER ::= { network 20 }
networkAliases							OBJECT IDENTIFIER ::= { network 27 }
networkPPPoE							OBJECT IDENTIFIER ::= { network 30 }
snmp									OBJECT IDENTIFIER ::= { cambiumpmp80211SystemConfiguration 5 }
cambiumSystem							OBJECT IDENTIFIER ::= { cambiumpmp80211SystemConfiguration 6 }
systemConfig							OBJECT IDENTIFIER ::= { cambiumSystem 1 }
systemNtpServer							OBJECT IDENTIFIER ::= { cambiumSystem 2 }
cambiumWebServer						OBJECT IDENTIFIER ::= { cambiumpmp80211SystemConfiguration 7 }
wireless								OBJECT IDENTIFIER ::= { cambiumpmp80211SystemConfiguration 8 }
wirelessDevice							OBJECT IDENTIFIER ::= { wireless 1 }
wirelessInterface						OBJECT IDENTIFIER ::= { wireless 2 }
wirelessPrefList						OBJECT IDENTIFIER ::= { wireless 3 }
wirelessMIRList							OBJECT IDENTIFIER ::= { wireless 4 }
wirelessRadius							OBJECT IDENTIFIER ::= { wireless 5 }
wirelessRadiusServerList				OBJECT IDENTIFIER ::= { wireless 6 }
wirelessRadiusCertificateList			OBJECT IDENTIFIER ::= { wireless 7 }
wirelessRadiusCertificateSet			OBJECT IDENTIFIER ::= { wireless 8 }
wirelessRadiusExtraCertificateSet		OBJECT IDENTIFIER ::= { wireless 9 }
multicast								OBJECT IDENTIFIER ::= { wireless 10 }
wirelessInterface2						OBJECT IDENTIFIER ::= { wireless 12 }
wlr										OBJECT IDENTIFIER ::= { wireless 13 }
wirelessRadiusCertificateListRow1		OBJECT IDENTIFIER ::= { wirelessRadiusCertificateList 1 }
wirelessRadiusCertificateListRow2		OBJECT IDENTIFIER ::= { wirelessRadiusCertificateList 2 }
wirelessRadiusCertificateListRow3		OBJECT IDENTIFIER ::= { wirelessRadiusCertificateList 3 }
l2Firewall								OBJECT IDENTIFIER ::= { cambiumpmp80211SystemConfiguration 9 }
l3Firewall								OBJECT IDENTIFIER ::= { cambiumpmp80211SystemConfiguration 10 }
confQoS									OBJECT IDENTIFIER ::= { cambiumpmp80211SystemConfiguration 11 }
dmz										OBJECT IDENTIFIER ::= { cambiumpmp80211SystemConfiguration 12 }
portForwarding							OBJECT IDENTIFIER ::= { cambiumpmp80211SystemConfiguration 13 }
vlans									OBJECT IDENTIFIER ::= { cambiumpmp80211SystemConfiguration 14 }
dlkm									OBJECT IDENTIFIER ::= { cambiumpmp80211SystemConfiguration 15 }
routing									OBJECT IDENTIFIER ::= { cambiumpmp80211SystemConfiguration 16 }
cambiumTelnetServer						OBJECT IDENTIFIER ::= { cambiumpmp80211SystemConfiguration 17 }
cambiumDeviceAgent						OBJECT IDENTIFIER ::= { cambiumpmp80211SystemConfiguration 20 }
upnpd									OBJECT IDENTIFIER ::= { cambiumpmp80211SystemConfiguration 21 }
lldpd									OBJECT IDENTIFIER ::= { cambiumpmp80211SystemConfiguration 23 }
mactelnet								OBJECT IDENTIFIER ::= { cambiumpmp80211SystemConfiguration 25 }
licensed								OBJECT IDENTIFIER ::= { cambiumpmp80211SystemConfiguration 27 }
tr069									OBJECT IDENTIFIER ::= { cambiumpmp80211SystemConfiguration 28 }
bonding									OBJECT IDENTIFIER ::= { cambiumpmp80211SystemConfiguration 30 }
accelerationEngine						OBJECT IDENTIFIER ::= { cambiumpmp80211SystemConfiguration 31 }
cambiumDCS								OBJECT IDENTIFIER ::= { cambiumpmp80211SystemConfiguration 32 }
cambiumGPSConfig						OBJECT IDENTIFIER ::= { cambiumpmp80211SystemConfiguration 33 }
vmsagent								OBJECT IDENTIFIER ::= { cambiumpmp80211SystemConfiguration 34 }
cambiumNSS								OBJECT IDENTIFIER ::= { cambiumpmp80211SystemConfiguration 35 }
dpi										OBJECT IDENTIFIER ::= { cambiumpmp80211SystemConfiguration 36 }
cambiumLinkTest							OBJECT IDENTIFIER ::= { cambiumpmp80211Tools 1 }
caminfo									OBJECT IDENTIFIER ::= { cambiumpmp80211Tools 2 }
cambiumToolBar							OBJECT IDENTIFIER ::= { cambiumpmp80211Tools 3 }
cambiumCfg								OBJECT IDENTIFIER ::= { cambiumpmp80211Tools 4 }
cambiumIDM								OBJECT IDENTIFIER ::= { cambiumpmp80211Tools 5 }
cambiumACSCfg							OBJECT IDENTIFIER ::= { cambiumpmp80211Tools 6 }
cambiumSpectral							OBJECT IDENTIFIER ::= { cambiumpmp80211Tools 7 }
cambiumArcher							OBJECT IDENTIFIER ::= { cambiumpmp80211Tools 8 }
cambiumWatchdog							OBJECT IDENTIFIER ::= { cambiumpmp80211Tools 9 }
cambiumCrashReporter					OBJECT IDENTIFIER ::= { cambiumpmp80211Tools 10 }
cambiumToolBarOpts						OBJECT IDENTIFIER ::= { cambiumToolBar 1 }
cambiumToolBarStates					OBJECT IDENTIFIER ::= { cambiumToolBar 2 }
watchdogRF								OBJECT IDENTIFIER ::= { cambiumWatchdog 6 }
watchdogGPS								OBJECT IDENTIFIER ::= { cambiumWatchdog 10 }
tr069Local								OBJECT IDENTIFIER ::= { tr069 1 }
tr069ACS								OBJECT IDENTIFIER ::= { tr069 2 }

cambiumCurrentSWInfo  OBJECT-TYPE
	SYNTAX	   DisplayString (SIZE(1..128))
	MAX-ACCESS read-only
	STATUS	   current
	DESCRIPTION
		"Software information - version, etc.
	 Device Allocation: AP, SM"
	::= { cambiumGeneralStatus 1 }

cambiumHWInfo  OBJECT-TYPE
	SYNTAX     Integer32 (-1..6|8..14|16..20|22|33..55|59..62|100..250|53264..53561)
	MAX-ACCESS read-only
	STATUS	   current
	DESCRIPTION
		"Hardware SKU:
			-1 - Not available
			0 - 5 GHz Connectorized Radio with Sync
			1 - 5 GHz Connectorized Radio
			2 - 5 GHz Integrated Radio
			3 - 2.4 GHz Connectorized Radio with Sync
			4 - 2.4 GHz Connectorized Radio
			5 - 2.4 GHz Integrated Radio
			6 - 5 GHz Force 200 (ROW)
			8 - 5 GHz Force 200 (FCC)
			9 - 2.4 GHz Force 200
			10 - ePMP 2000
			11 - 5 GHz Force 180 (ROW)
			12 - 5 GHz Force 180 (FCC)
			13 - 5 GHz Force 190 Radio (ROW/ETSI)
			14 - 5 GHz Force 190 Radio (FCC)
			16 - 6 GHz Force 180 Radio
			17 - 6 GHz Connectorized Radio with Sync
			18 - 6 GHz Connectorized Radio
			19 - 2.5 GHz Connectorized Radio with Sync
			20 - 2.5 GHz Connectorized Radio
			22 - 5 GHz Force 130 Radio
			23 - 2.4 GHz Force 130 Radio
			24 - 5 GHz Force 200L Radio
			25 - 5 GHz Force 200L Radio V2
			33  - 5 GHz PTP550 Integrated Radio
			34  - 5 GHz PTP550 Connectorized Radio
			35  - 5 GHz Force 300-25 Radio (FCC)
			36  - 5 GHz Force 300-25 Radio (ROW/ETSI)
			37  - ePMP3000 (FCC)
			38  - 5 GHz Force 300-16 Radio (FCC)
			39  - 5 GHz Force 300-16 Radio (ROW/ETSI)
			40  - ePMP3000 (ROW/ETSI)
			41  - 5 GHz PTP 550E Integrated Radio
			42  - 5 GHz PTP 550E Connectorized Radio
			43  - 5 GHz ePMP3000L (FCC)
			44  - 5 GHz ePMP3000L (ROW/ETSI)
			45  - 5 GHz Force 300 Connectorized Radio without GPS (FCC)
			46  - 5 GHz Force 300 Connectorized Radio without GPS (ROW/ETSI)
			47  - 5 GHz Force 300-13 Radio (FCC)
			48  - 5 GHz Force 300-13 Radio (ROW/ETSI)
			49  - 5 GHz Force 300-19 Radio (FCC)
			50  - 5 GHz Force 300-19 Radio (ROW/ETSI)
			51  - 5 GHz Force 300-19R IP67 Radio (ROW/ETSI)
			52  - 5 GHz Force 300-19R IP67 Radio (FCC)
			53  - 5 GHz ePMP Client MAXrP IP67 Radio (FCC)
			54  - 5 GHz ePMP Client MAXrP IP67 Radio (ROW/ETSI)
			55  - 5 GHz Force 300-25 Radio V2 (FCC)
			58  - 5 GHz Force 300-25L Radio
			59  - 5 GHz Force 300 CSML Connectorized Radio
			60  - 5 GHz Force 300-25L Radio V2
			61  - 5 GHz Force 300-13L Radio
			62  - 5 GHz ePMP MP 3000
			100 - (0xe855) ePMP Elevate NSM5-XW
			110 - (0xe845) ePMP Elevate NSlocoM5-XW
			111 - (0xe8a2) ePMP Elevate NSlocoM2-XW
			112 - (0xe867) ePMP Elevate NSlocoM2-V2-XW
			113 - (0xe866) ePMP Elevate NSlocoM2-V3-XW
			120 - (0xe6b5) ePMP Elevate RM5-XW-V1
			121 - (0xe3b5) ePMP Elevate RM5-XW-V2
			130 - (0xe815) ePMP Elevate NBE-M5-16-XW
			131 - (0xe825) ePMP Elevate NBE-M5-19-XW
			132 - (0xe812) ePMP Elevate NBE-M2-13-XW
			140 - ePMP Elevate SXTLITE5 BOARD
			141 - ePMP Elevate INTELBRAS BOARD
			142 - ePMP Elevate LHG5 BOARD
			143 - ePMP Elevate Disc Lite BOARD
			144 - ePMP Elevate 911L BOARD
			145 - ePMP Elevate Sextant BOARD
			150 - (0xe3e5) ePMP Elevate PBE-M5-300-XW
			151 - (0xe4e5) ePMP Elevate PBE-M5-400-XW
			152 - (0xe885) ePMP Elevate PBE-M5-620-XW
			153 - (0xe2c2) ePMP Elevate PBE-M2-400-XW
			154 - (0xe6e5) ePMP Elevate PBE-M5-400-ISO-XW
			155 - (0xe5e5) ePMP Elevate PBE-M5-300-ISO-XW
			156 - (0xe7e5) ePMP Elevate PBE-M5-600-ISO-XW
			160 - (0xe835) ePMP Elevate AG-HP-5G-XW
			161 - (0xe832) ePMP Elevate AG-HP-2G-XW
			162 - (0xe865) ePMP Elevate LB-M5-23-XW
			170 - (0xe005) ePMP Elevate NSM5-XM-V1
			171 - (0xe805) ePMP Elevate NSM5-XM-V2
			173 - (0xe012) ePMP Elevate NS-M2-V1
			176 - (0xe002) ePMP Elevate NS-M2-V2
			180 - (0xe0a5) ePMP Elevate NSlocoM5-XM-V1
			181 - (0xe8a5) ePMP Elevate NSlocoM5-XM-V2
			183 - (0xe0a2) ePMP Elavate NSloco-M2
			193 - (0xe2b5) ePMP Elevate NB-5G22-XM
			194 - (0xe2e5) ePMP Elevate NB-5G25-XM
			195 - (0xe235) ePMP Elevate NB-XM
			196 - (0xe2b2) ePMP Elevate NB-M2-V1-XM
			197 - (0xe232) ePMP Elevate NB-M2-V2-XM
			200 - ePMP Elevate INTELBRAS WOM-5A-MiMo BOARD
			201 - ePMP Elevate INTELBRAS WOM-5A-23 BOARD
			220 - (0xe006) ePMP Elevate NS-M6
			230 - (0xe215) ePMP Elevate AG-M5-23-XM
			231 - (0xe245) ePMP Elevate AG-M5-28-XM
			232 - (0xe255) ePMP Elevate AG-HP-5G-XM
			233 - (0xe212) ePMP Elevate AG-M2-16-XM
			234 - (0xe242) ePMP Elevate AG-M2-20-XM
			235 - (0xe252) ePMP Elevate AG-M2-HP-XM
			236 - (0xe202) ePMP Elevate BM-M2-HP-XM
			237 - (0xe205) ePMP Elevate BM-M5-HP-XM
			241 - (0xe105) ePMP Elevate RM5-V1-XM
			242 - (0xe1b5) ePMP Elevate RM5-V2-XM
			243 - (0xe1c5) ePMP Elevate RM5-V3-XM
			244 - (9xe8b5) ePMP Elevate RM5-V4-XM
			245 - (0xe102) ePMP Elevate RM2-V1-XM
			246 - (0xe112) ePMP Elevate RM2-V2-XM
			247 - (0xe1b2) ePMP Elevate RM2-V3-XM
			248 - (0xe1c2) ePMP Elevate RM2-V4-XM
			53264 - 6 GHz ePMP 4600 4x4 (ROW/FCC)
			53280 - 5 GHz ePMP 4500 8x8 (ROW)
			53281 - 5 GHz ePMP 4500C 8x8 (ROW)
			53288 - 5 GHz ePMP 4500 8x8 (FCC)
			53289 - 5 GHz ePMP 4500C 8x8 (FCC)
			53296 - 6 GHz ePMP 4600L (ROW/FCC)
			53344 - 5 GHz ePMP 4500L (ROW)
			53352 - 5 GHz ePMP 4500L (FCC)
			53376 - 5 GHz cnPilot Tiger
			53504 - 5 GHz Force 425 (ROW)
			53505 - 5 GHz Force 400C (ROW)
			53512 - 5 GHz Force 425 (FCC)
			53513 - 5 GHz Force 400C (FCC)
			53520 - 6 GHz Force 4600C (ROW/FCC)
			53536 - 5 GHz Force 4516 (ROW)
			53537 - 5 GHz Force 4525 (ROW)
			53538 - 5 GHz Force 4525L (ROW)
			53544 - 5 GHz Force 4516 (FCC)
			53545 - 5 GHz Force 4525 (FCC)
			53552 - 6 GHz Force 4616 (ROW)
			53553 - 6 GHz Force 4625 (ROW)
			53560 - 6 GHz Force 4616 USB GPS Radio (FCC)
			53561 - 6 GHz Force 4625 USB GPS Radio (FCC)
		Device Allocation: AP, SM"
	::= { cambiumGeneralStatus 2 }

cambiumDateTime	 OBJECT-TYPE
	SYNTAX	   DisplayString (SIZE(1..128))
	MAX-ACCESS read-only
	STATUS	   current
	DESCRIPTION
		"Date and Time in format mm/dd/yyyy:hh:mm:ss
		Device Allocation: AP, SM"
	::= { cambiumGeneralStatus 3 }

cambiumSystemUptime	 OBJECT-TYPE
	SYNTAX	   DisplayString (SIZE(1..128))
	MAX-ACCESS read-only
	STATUS	   current
	DESCRIPTION
		"Device UpTime in format days, hours, minutes, and seconds -> dddd:hh:mm:ss
		Device Allocation: AP, SM"
	::= { cambiumGeneralStatus 4 }

cambiumWirelessMACAddress  OBJECT-TYPE
	SYNTAX	   DisplayString (SIZE(11..17))
	MAX-ACCESS read-only
	STATUS	   current
	DESCRIPTION
		"The device Wireless MAC address
		Device Allocation: AP, SM"
	::= { cambiumGeneralStatus 5 }

cambiumDFSStatus  OBJECT-TYPE
	SYNTAX	   Integer32 (1..6)
	MAX-ACCESS read-only
	STATUS	   current
	DESCRIPTION
		"DFS Status:
			1 - N/A,
			2 - Channel Availability Check,
			3 - In-Service,
			4 - Radar Signal Detected,
			5 - In-Service Monitoring at Alternative Channel,
			6 - System Not In Service due to DFS
		Device Allocation: AP, SM"
	::= { cambiumGeneralStatus 6 }

cambiumEffectiveSyncSource OBJECT-TYPE
	SYNTAX	   Integer32 (1|2|3|4|5)
	MAX-ACCESS read-only
	STATUS	   current
	DESCRIPTION
		"Sync Source Status:
			1 - GPS Sync Up,
			2 - GPS Sync Down,
			3 - CMM4 Sync,
			4 - CMM3 Sync,
			5 - CMM5 Sync
		Device Allocation: AP"
	::= { cambiumGeneralStatus 7 }

cambiumEffectiveCountryCode OBJECT-TYPE
	SYNTAX	   DisplayString (SIZE(2))
	MAX-ACCESS read-only
	STATUS	   current
	DESCRIPTION
		"Current device Country Code
		Device Allocation: AP, SM"
	::= { cambiumGeneralStatus 8 }

cambiumEffectiveAntennaGain OBJECT-TYPE
	SYNTAX	   Integer32 (0..40)
	MAX-ACCESS read-only
	STATUS	   current
	DESCRIPTION
		"Effective Antenna Gain in dBi
		Device Allocation: AP, SM"
	::= { cambiumGeneralStatus 9 }

cambiumEffectiveTDDRatio OBJECT-TYPE
	SYNTAX     Integer32 (1|2|3|4|35|40|45|55|60|65|70)
	MAX-ACCESS read-only
	STATUS	   current
	DESCRIPTION
		"Effective DL/UL Ratio:
			1  - 75/25,
			2  - 50/50,
			3  - 30/70,
			4  - Flexible,
			35 - 35/65,
			40 - 40/60,
			45 - 45/55,
			55 - 55/45,
			60 - 60/40,
			65 - 65/35,
			70 - 70/30
		Device Allocation: AP, SM"
	::= { cambiumGeneralStatus 10 }

cambiumEffectiveSSID OBJECT-TYPE
	SYNTAX	   DisplayString (SIZE(0..128))
	MAX-ACCESS read-only
	STATUS	   current
	DESCRIPTION
		"Effective SSID
		Device Allocation: AP"
	::= { cambiumGeneralStatus 11 }

cambiumEffectiveAuthenticationType OBJECT-TYPE
	SYNTAX	   Integer32 (0|1|2|3)
	MAX-ACCESS read-only
	STATUS	   current
	DESCRIPTION
		"Effective Authentication Type:
			1 - Open,
			2 - WPA2,
			3 - EAP-TTLS"
	::= { cambiumGeneralStatus 12 }

cambiumEffectiveDeviceName OBJECT-TYPE
	SYNTAX	   DisplayString (SIZE(0..128))
	MAX-ACCESS read-only
	STATUS	   current
	DESCRIPTION
		"Effective Device Name
		Device Allocation: AP, SM"
	::= { cambiumGeneralStatus 13 }

cambiumUbootVersion OBJECT-TYPE
	SYNTAX	   DisplayString (SIZE(0..128))
	MAX-ACCESS read-only
	STATUS	   current
	DESCRIPTION
		"U-boot version
		Device Allocation: AP, SM"
	::= { cambiumGeneralStatus 14 }

cambiumLANMACAddress  OBJECT-TYPE
	SYNTAX	   DisplayString (SIZE(11..17))
	MAX-ACCESS read-only
	STATUS	   current
	DESCRIPTION
		"The device LAN MAC address
		Device Allocation: AP, SM"
	::= { cambiumGeneralStatus 15 }

cambiumCurrentuImageIVersion OBJECT-TYPE
	SYNTAX	   DisplayString (SIZE(0..20))
	MAX-ACCESS read-only
	STATUS	   current
	DESCRIPTION
		"Version of firmware on uimagei partition
		Device Allocation: AP"
	::= { cambiumGeneralStatus 16 }

cambiumCurrentuImageVersion OBJECT-TYPE
	SYNTAX	   DisplayString (SIZE(0..20))
	MAX-ACCESS read-only
	STATUS	   current
	DESCRIPTION
		"Version of firmware on uimage partition
		Device Allocation: AP, SM"
	::= { cambiumGeneralStatus 17 }

cambiumDeviceLatitude OBJECT-TYPE
	SYNTAX	   DisplayString
	MAX-ACCESS read-only
	STATUS	   current
	DESCRIPTION
		"Current location information. GPS cordinates (latitude).
		Device Allocation: AP, SM"
	::= { cambiumGeneralStatus 18 }

cambiumDeviceLongitude OBJECT-TYPE
	SYNTAX	   DisplayString
	MAX-ACCESS read-only
	STATUS	   current
	DESCRIPTION
		"Current location information.GPS cordinates (longitude).
		Device Allocation: AP, SM"
	::= { cambiumGeneralStatus 19 }

sysRebootCounter OBJECT-TYPE
	SYNTAX	   Integer32
	MAX-ACCESS read-only
	STATUS	   current
	DESCRIPTION
		"Device Reboot Counter
		Device Allocation: AP, SM"
	::= { cambiumGeneralStatus 20 }

cambiumDFSStatusStr	 OBJECT-TYPE
	SYNTAX	   DisplayString (SIZE(0..128))
	MAX-ACCESS read-only
	STATUS	   current
	DESCRIPTION
		"DFS Status (text)
		Device Allocation: AP, SM"
	::= { cambiumGeneralStatus 21 }

cambiumDriverType  OBJECT-TYPE
	SYNTAX	   Integer32 (1|2)
	MAX-ACCESS read-only
	STATUS	   current
	DESCRIPTION
		"SM current driver (TDD - 1, standard Wi-Fi - 2).
		Device Allocation: SM"
	::= { cambiumGeneralStatus 22 }

cambiumSFPMACAddress  OBJECT-TYPE
	SYNTAX	   DisplayString (SIZE(11..17))
	MAX-ACCESS read-only
	STATUS	   current
	DESCRIPTION
		"The device SFP MAC address
		Device Allocation: AP, SM"
	::= { cambiumGeneralStatus 23 }

sysSoftRebootCounter OBJECT-TYPE
	SYNTAX	   Integer32
	MAX-ACCESS read-only
	STATUS	   current
	DESCRIPTION
		"Device Software Reboot Counter
		Device Allocation: AP, SM"
	::= { cambiumGeneralStatus 25 }

sysHardRebootCounter OBJECT-TYPE
	SYNTAX	   Integer32
	MAX-ACCESS read-only
	STATUS	   current
	DESCRIPTION
		"Device Hardware Reboot Counter
		Device Allocation: AP, SM"
	::= { cambiumGeneralStatus 26 }

sysConfigFlashStatus OBJECT-TYPE
	SYNTAX     Integer32
	MAX-ACCESS read-only
	STATUS     current
	DESCRIPTION
		"Hardware config partition state:
		  1 - Healthy
		  2 - Broken, Flash formatted, Configuration lost
		  3 - Broken, Flash unrecoverable, Configuration may last until upgrade
		 Device Allocation: AP, SM"
	::= { cambiumGeneralStatus 27 }

sysWDTRebootCounter OBJECT-TYPE
	SYNTAX     Integer32
	MAX-ACCESS read-only
	STATUS     current
	DESCRIPTION
		"Device Watchdog Reboot Counter
		 Device Allocation: AP, SM"
	::= { cambiumGeneralStatus 28 }

cambiumESN	OBJECT-TYPE
	SYNTAX	   DisplayString (SIZE(13))
	MAX-ACCESS read-only
	STATUS	   current
	DESCRIPTION
		"Device' serial number (ESN), based on MAC address
		Device Allocation: AP, SM"
	::= { cambiumGeneralStatus 30 }

cambiumEPMPMSN OBJECT-TYPE
	SYNTAX	   DisplayString (SIZE(0|12))
	MAX-ACCESS read-only
	STATUS	   current
	DESCRIPTION
		"CNS MSN serial number: AP, SM"
	::= { cambiumGeneralStatus 31 }

cambiumFactoryReset OBJECT-TYPE
	SYNTAX	   Integer32 (0|1)
	MAX-ACCESS read-only
	STATUS	   current
	DESCRIPTION
		"Factory Reset feature state.
		Default allocation: AP, SM"
	::= { cambiumGeneralStatus 32 }

cambiumSubModeType OBJECT-TYPE
	SYNTAX	   Integer32 (1|2|3|4|5|6)
	MAX-ACCESS read-only
	STATUS	   current
	DESCRIPTION
		"Protocol (Sub) Mode type:
			1 - TDD,
			2 - TDD PTP,
			3 - Standard WiFi,
			4 - ePTP Slave,
			5 - ePTP Master,
			6 - WLR,
		Device Allocation: AP, SM"
	::= { cambiumGeneralStatus 33 }

cambiumDAVersion OBJECT-TYPE
	SYNTAX     DisplayString (SIZE(8))
	MAX-ACCESS read-only
	STATUS     current
	DESCRIPTION
		"cnMaestro Device-Agent version.
		Device Allocation: AP, SM"
	::= { cambiumGeneralStatus 35 }

ePMP2000PowerSupplyStatus OBJECT-TYPE
	SYNTAX	   Integer32 (1|2)
	MAX-ACCESS read-only
	STATUS	   current
	DESCRIPTION
		"ePMP2000/ePMP3000: Power supply status
		Device Allocation: AP"
	::= { cambiumGeneralStatus 40 }

ePMP2000SmartAntennaStatus OBJECT-TYPE
	SYNTAX	   Integer32 (0|1|2|3)
	MAX-ACCESS read-only
	STATUS	   current
	DESCRIPTION
		"ePMP2000/ePMP3000 Smart antenna state
		Bit 0 - Smart Antenna powered, Bit 1 - Smart Antenna detected
		0 - Disabled
		1 - Enabled
		Device Allocation: AP"
	::= { cambiumGeneralStatus 41 }

ePMP2000ULAntennaStatus OBJECT-TYPE
	SYNTAX     Integer32 (0|1|2|3)
	MAX-ACCESS read-only
	STATUS     current
	DESCRIPTION
		"ePMP2000/ePMP3000 Uplink antenna state
		Bit 0 - Forced Antenna, Bit 1 - Smart Antenna Active
		0 - Disabled
		1 - Enabled
		Device Allocation: AP"
	::= { cambiumGeneralStatus 42 }

ePMP2000FPGALoadStatus OBJECT-TYPE
	SYNTAX     Integer32 (-31..1)
	MAX-ACCESS read-only
	STATUS     current
	DESCRIPTION
		"ePMP2000/ePMP3000: FPGA Load Status:
		  1 - FPGA loaded successfully
		  0 - Undefined error
		 -1 - Initialize algorithm file fail
		 -2 - Initialize data file fail
		 -3 - Version not supported
		 -4 - Header checksum fail
		 -5 - Initialize SPI fail
		 -6 - Initialization fail
		 -7 - IDCODE verification fail
		 -8 - USERCODE verification fail
		 -9 - SED CRC verification fail
		 -10 - TAG Memory verification fail
		 -11 - Incorrect algorithm format
		 -12 - Invalid data
		 -13 - Hardware fail
		 -14 - LOOP condition fail
		 -20 - Verification fail
		 -30 - FPGA has invalid firmware
		 -31 - System use current FPGA firmware
		Device Allocation: AP"
	::= { cambiumGeneralStatus 43 }

cambiumSTAForceAntennaSelection OBJECT-TYPE
	SYNTAX	   Integer32 (0|1)
	MAX-ACCESS read-only
	STATUS	   current
	DESCRIPTION
		"is forcing antenna allowed on station
		1 - force antenna allowed on STA
		0 - force antenna forbidden
		Device Allocation: AP"
	::= { cambiumGeneralStatus 44 }

cambiumSTALinktestForceSelection OBJECT-TYPE
	SYNTAX	   Integer32 (0|1)
	MAX-ACCESS read-only
	STATUS	   current
	DESCRIPTION
		"is forcing antenna allowed on station
		during link_test
		1 - force antenna allowed on STA
		0 - force antenna forbidden
		Device Allocation: AP, SM"
	::= { cambiumGeneralStatus 45 }

cambiumEffectiveNTPServers	 OBJECT-TYPE
	SYNTAX	   IpAddress
	MAX-ACCESS read-only
	STATUS	   current
	DESCRIPTION
		"Effective NTP Server
		Device Allocation: AP, SM"
	::= { cambiumGeneralStatus 46 }

cambiumNTPDateState	 OBJECT-TYPE
	SYNTAX	   Integer32 (0|1|2)
	MAX-ACCESS read-only
	STATUS	   current
	DESCRIPTION
		"NTP date state:
			0 - NTP Disabled
			1 - NTP Enabled, Date and Time is not obtained
			2 - NTP Enabled, Date and Time is obtained from NTP Server
		Device Allocation: AP, SM"
	::= { cambiumGeneralStatus 47 }

cambiumMCUVersion  OBJECT-TYPE
	SYNTAX	   DisplayString (SIZE(1..128))
	MAX-ACCESS read-only
	STATUS	   current
	DESCRIPTION
		"MCU software information - version, etc.
	 Device Allocation: AP, SM"
	::= { cambiumGeneralStatus 50 }

cambiumWireless2MACAddress  OBJECT-TYPE
	SYNTAX	   DisplayString (SIZE(11..17))
	MAX-ACCESS read-only
	STATUS	   current
	DESCRIPTION
		"The device Second Radio Wireless MAC address
		Device Allocation: AP, SM"
	::= { cambiumGeneralStatus 51 }

cambiumDFS2Status  OBJECT-TYPE
	SYNTAX     Integer32 (1..6)
	MAX-ACCESS read-only
	STATUS     current
	DESCRIPTION
		"DFS Status:
			1 - N/A,
			2 - Channel Availability Check,
			3 - In-Service,
			4 - Radar Signal Detected,
			5 - In-Service Monitoring at Alternative Channel,
			6 - System Not In Service due to DFS
		Device Allocation: AP, SM"
	::= { cambiumGeneralStatus 52 }

cambiumEffectiveSSID2 OBJECT-TYPE
	SYNTAX     DisplayString (SIZE(0..128))
	MAX-ACCESS read-only
	STATUS     current
	DESCRIPTION
		"Effective SSID
		Device Allocation: AP"
	::= { cambiumGeneralStatus 53 }

cambiumDFS2StatusStr  OBJECT-TYPE
	SYNTAX     DisplayString (SIZE(0..128))
	MAX-ACCESS read-only
	STATUS     current
	DESCRIPTION
		"DFS Status (text)
		Device Allocation: AP, SM"
	::= { cambiumGeneralStatus 54 }

crashReporterKernelDataAvailable  OBJECT-TYPE
	SYNTAX		Integer32 (0|1)
	MAX-ACCESS	read-only
	STATUS		current
	DESCRIPTION
		"Kernel crash data available for use
			1 - data is available,
			0 - data is not available
		Device Allocation: AP, SM"
	::= { cambiumGeneralStatus 55 }

cambiumTR069Status OBJECT-TYPE
	SYNTAX     Integer32 (0..2)
	MAX-ACCESS read-only
	STATUS     current
	DESCRIPTION
		"TR-069 Status:
			0 - not connected to ACS
			1 - connected to ACS
			2 - XMPP session is established
		Device Allocation: AP, SM"
	::= { cambiumGeneralStatus 56 }

cambiumDPIStatus OBJECT-TYPE
	SYNTAX		Integer32 (0|1)
	MAX-ACCESS	read-only
	STATUS		current
	DESCRIPTION
		"DPI status
			1 - packets processing is enabled,
			0 - packets processing is disabled
		Device Allocation: AP, SM"
	::= { cambiumGeneralStatus 57 }


cambiumSTAConnectedRFFrequency OBJECT-TYPE
	SYNTAX	   Integer32 (2355..6420)
	MAX-ACCESS read-only
	STATUS	   current
	DESCRIPTION
		"The frequency connected to AP
		Device Allocation: AP, SM"
	::= { cambiumRFStatus 1 }

cambiumSTAConnectedRFBandwidth OBJECT-TYPE
	SYNTAX	   Integer32 (1|2)
	MAX-ACCESS read-only
	STATUS	   current
	DESCRIPTION
		"Connected RF Bandwidth:
			1 for 20 MHz,
			2 for 40 MHz,
			3 for 10 MHz,
			4 for 5  MHz,
			5 for 80 MHz
		Device Allocation: SM"
	::= { cambiumRFStatus 2 }

cambiumSTADLRSSI OBJECT-TYPE
	SYNTAX	   Integer32
	MAX-ACCESS read-only
	STATUS	   current
	DESCRIPTION
		"SM RSSI in dBm
		Device Allocation: SM"
	::= { cambiumRFStatus 3 }

cambiumSTADLCINR OBJECT-TYPE
	SYNTAX	   Integer32
	MAX-ACCESS read-only
	STATUS	   obsolete
	DESCRIPTION
		"SM CINR in dBm
		Device Allocation: SM"
	::= { cambiumRFStatus 4 }

cambiumSTAConductedTXPower OBJECT-TYPE
	SYNTAX	   Integer32 (-25..30)
	MAX-ACCESS read-only
	STATUS	   current
	DESCRIPTION
		"Current TX Power (Board Output Conducted) in dBm
		Device Allocation: SM"
	::= { cambiumRFStatus 5 }

cambiumSTAUplinkMCSMode OBJECT-TYPE
	SYNTAX	   Integer32
	MAX-ACCESS read-only
	STATUS	   current
	DESCRIPTION
		"UL MCS Mode:
			This parameter represents Uplink MCS mode number for both 802.11n and 802.11ac standard devices.
			And Uplink MCS Rate for 802.11ax standard devices.

			802.11n HW:

			1  for MCS1,
			2  for MCS2,
			3  for MCS3,
			4  for MCS4,
			5  for MCS5,
			6  for MCS6,
			7  for MCS7,
			9  for MCS9,
			10 for MCS10,
			11 for MCS11,
			12 for MCS12,
			13 for MCS13,
			14 for MCS14,
			15 for MCS15,

			802.11ac HW:

			20 for 'SS MCS 0 - BPSK 1/2',
			21 for 'SS MCS 1 - QPSK 1/2',
			22 for 'SS MCS 2 - QPSK 3/4',
			23 for 'SS MCS 3 - 16-QAM 1/2',
			24 for 'SS MCS 4 - 16-QAM 3/4',
			25 for 'SS MCS 5 - 64-QAM 2/3',
			26 for 'SS MCS 6 - 64-QAM 3/4',
			27 for 'SS MCS 7 - 64-QAM 5/6',
			28 for 'SS MCS 8 - 256-QAM 3/4',
			29 for 'SS MCS 9 - 256-QAM 5/6',

			30 for 'DS MCS 0 - BPSK 1/2',
			31 for 'DS MCS 1 - QPSK 1/2',
			32 for 'DS MCS 2 - QPSK 3/4',
			33 for 'DS MCS 3 - 16-QAM 1/2',
			34 for 'DS MCS 4 - 16-QAM 3/4',
			35 for 'DS MCS 5 - 64-QAM 2/3',
			36 for 'DS MCS 6 - 64-QAM 3/4',
			37 for 'DS MCS 7 - 64-QAM 5/6',
			38 for 'DS MCS 8 - 256-QAM 3/4',
			39 for 'DS MCS 9 - 256-QAM 5/6',

			802.11ax HW:

			MCS rate on AX is in range of 100-813 and organized using the following format:
			100 for 'SS MCS 0 - BPSK 1/2',
			101 for 'SS MCS 1 - QPSK 1/2',
			102 for 'SS MCS 2 - QPSK 3/4',
			103 for 'SS MCS 3 - 16-QAM 1/2',
			104 for 'SS MCS 4 - 16-QAM 3/4',
			105 for 'SS MCS 5 - 64-QAM 2/3',
			106 for 'SS MCS 6 - 64-QAM 3/4',
			107 for 'SS MCS 7 - 64-QAM 5/6',
			108 for 'SS MCS 8 - 256-QAM 3/4',
			109 for 'SS MCS 9 - 256-QAM 5/6',
			110 for 'SS MCS 10- 1024-QAM 3/4',
			111 for 'SS MCS 11- 1024-QAM 5/6',
			112 for 'SS MCS 12- 4096-QAM 3/4',
			113 for 'SS MCS 13- 4096-QAM 5/6',

			200 for 'DS MCS 0 - BPSK 1/2',
			201 for 'DS MCS 1 - QPSK 1/2',
			202 for 'DS MCS 2 - QPSK 3/4',
			203 for 'DS MCS 3 - 16-QAM 1/2',
			204 for 'DS MCS 4 - 16-QAM 3/4',
			205 for 'DS MCS 5 - 64-QAM 2/3',
			206 for 'DS MCS 6 - 64-QAM 3/4',
			207 for 'DS MCS 7 - 64-QAM 5/6',
			208 for 'DS MCS 8 - 256-QAM 3/4',
			209 for 'DS MCS 9 - 256-QAM 5/6',
			210 for 'DS MCS 10- 1024-QAM 3/4',
			211 for 'DS MCS 11- 1024-QAM 5/6',
			212 for 'DS MCS 12- 4096-QAM 3/4',
			213 for 'DS MCS 13- 4096-QAM 5/6',

		Device Allocation: SM"
	::= { cambiumRFStatus 6 }

cambiumSTADownlinkMCSMode OBJECT-TYPE
	SYNTAX	   Integer32
	MAX-ACCESS read-only
	STATUS	   current
	DESCRIPTION
		"DL MCS Mode:
			This parameter represents Downlink MCS mode number for both 802.11n and 802.11ac standard devices.
			And Uplink MCS Rate for 802.11ax standard devices.

			802.11n HW:

			1  for MCS1,
			2  for MCS2,
			3  for MCS3,
			4  for MCS4,
			5  for MCS5,
			6  for MCS6,
			7  for MCS7,
			9  for MCS9,
			10 for MCS10,
			11 for MCS11,
			12 for MCS12,
			13 for MCS13,
			14 for MCS14,
			15 for MCS15,

			802.11ac HW:

			20 for 'SS MCS 0 - BPSK 1/2',
			21 for 'SS MCS 1 - QPSK 1/2',
			22 for 'SS MCS 2 - QPSK 3/4',
			23 for 'SS MCS 3 - 16-QAM 1/2',
			24 for 'SS MCS 4 - 16-QAM 3/4',
			25 for 'SS MCS 5 - 64-QAM 2/3',
			26 for 'SS MCS 6 - 64-QAM 3/4',
			27 for 'SS MCS 7 - 64-QAM 5/6',
			28 for 'SS MCS 8 - 256-QAM 3/4',
			29 for 'SS MCS 9 - 256-QAM 5/6',

			30 for 'DS MCS 0 - BPSK 1/2',
			31 for 'DS MCS 1 - QPSK 1/2',
			32 for 'DS MCS 2 - QPSK 3/4',
			33 for 'DS MCS 3 - 16-QAM 1/2',
			34 for 'DS MCS 4 - 16-QAM 3/4',
			35 for 'DS MCS 5 - 64-QAM 2/3',
			36 for 'DS MCS 6 - 64-QAM 3/4',
			37 for 'DS MCS 7 - 64-QAM 5/6',
			38 for 'DS MCS 8 - 256-QAM 3/4',
			39 for 'DS MCS 9 - 256-QAM 5/6',

			802.11ax HW:

			MCS rate on AX is in range of 100-811 and organized in the following format:
			MCS rate on AX is in range of 100-813 and organized using the following format:
			100 for 'SS MCS 0 - BPSK 1/2',
			101 for 'SS MCS 1 - QPSK 1/2',
			102 for 'SS MCS 2 - QPSK 3/4',
			103 for 'SS MCS 3 - 16-QAM 1/2',
			104 for 'SS MCS 4 - 16-QAM 3/4',
			105 for 'SS MCS 5 - 64-QAM 2/3',
			106 for 'SS MCS 6 - 64-QAM 3/4',
			107 for 'SS MCS 7 - 64-QAM 5/6',
			108 for 'SS MCS 8 - 256-QAM 3/4',
			109 for 'SS MCS 9 - 256-QAM 5/6',
			110 for 'SS MCS 10- 1024-QAM 3/4',
			111 for 'SS MCS 11- 1024-QAM 5/6',
			112 for 'SS MCS 12- 4096-QAM 3/4',
			113 for 'SS MCS 13- 4096-QAM 5/6',

			200 for 'DS MCS 0 - BPSK 1/2',
			201 for 'DS MCS 1 - QPSK 1/2',
			202 for 'DS MCS 2 - QPSK 3/4',
			203 for 'DS MCS 3 - 16-QAM 1/2',
			204 for 'DS MCS 4 - 16-QAM 3/4',
			205 for 'DS MCS 5 - 64-QAM 2/3',
			206 for 'DS MCS 6 - 64-QAM 3/4',
			207 for 'DS MCS 7 - 64-QAM 5/6',
			208 for 'DS MCS 8 - 256-QAM 3/4',
			209 for 'DS MCS 9 - 256-QAM 5/6',
			210 for 'DS MCS 10- 1024-QAM 3/4',
			211 for 'DS MCS 11- 1024-QAM 5/6',
			212 for 'DS MCS 12- 4096-QAM 3/4',
			213 for 'DS MCS 13- 4096-QAM 5/6',

		Device Allocation: SM"
	::= { cambiumRFStatus 7 }

cambiumSTAConnectedAP OBJECT-TYPE
	SYNTAX	   DisplayString (SIZE(1..128))
	MAX-ACCESS read-only
	STATUS	   current
	DESCRIPTION
		"Connected AP Name (SSID), If no AP is connected, Scanning should be returned
		Device Allocation: SM"
	::= { cambiumRFStatus 8 }

cambiumSTAPowerControlMode OBJECT-TYPE
	SYNTAX	   Integer32 (-1|0|1|2)
	MAX-ACCESS read-only
	STATUS	   current
	DESCRIPTION
		"Power Control Mode on SM:
			-1 - No Value,
			0 - Disable,
			1 - Open Loop,
			2 - Close Loop
		Device Allocation: SM"
	::= { cambiumRFStatus 9 }

cambiumAPNumberOfConnectedSTA OBJECT-TYPE
	SYNTAX	   Integer32 (1..128)
	MAX-ACCESS read-only
	STATUS	   current
	DESCRIPTION
		"Number Of connected stations
		Device Allocation: AP"
	::= { cambiumRFStatus 10 }

cambiumAPConnectedSTAListTable OBJECT-TYPE
	SYNTAX	   SEQUENCE OF CambiumAPConnectedSTAListEntry
	MAX-ACCESS not-accessible
	STATUS	   obsolete
	DESCRIPTION
		"This table contains information relevant to the Connected Subscriber Modules:
			Subscriber Module MAC Address,
			Subscriber Module AID,
			Subscriber Module Channel,
			UL RSSI per SM,
			DL RSSI per SM,
			DL CINR per SM,
			UL CINR per SM,
			UL MCS Mode per SM,
			DL MCS Mode per SM,
			Subscriber Module IP Address
		Device Allocation: AP"
	::= { cambiumRFStatus 11 }

cambiumAPConnectedSTAListEntry OBJECT-TYPE
	SYNTAX	   CambiumAPConnectedSTAListEntry
	MAX-ACCESS not-accessible
	STATUS	   obsolete
	DESCRIPTION
		"Wireless parameters mapping for particular station.
		Device Allocation: AP"
	INDEX	{ cambiumAPNumberOfConnectedSTA }
	::= { cambiumAPConnectedSTAListTable 1 }

CambiumAPConnectedSTAListEntry ::= SEQUENCE {
	connectedSTAListMAC			DisplayString,
	connectedSTAListAID			Integer32,
	connectedSTAListChannel		Integer32,
	connectedSTAListULRSSI		Integer32,
	connectedSTAListDLRSSI		Integer32,
	connectedSTAListULCINR		Integer32,
	connectedSTAListDLCINR		Integer32,
	connectedSTAListULMCS		Integer32,
	connectedSTAListDLMCS		Integer32,
	connectedSTAListIP			IpAddress,
	connectedSTAListMirSrc		DisplayString,
	connectedSTAListMirULRate	DisplayString,
	connectedSTAListMirDLRate	DisplayString
}

connectedSTAListMAC OBJECT-TYPE
	SYNTAX	   DisplayString (SIZE(0|11..17))
	MAX-ACCESS read-only
	STATUS	   obsolete
	DESCRIPTION
		"Connected SM WLAN MAC Address
		Device Allocation: AP"
	::= { cambiumAPConnectedSTAListEntry 1 }

connectedSTAListAID OBJECT-TYPE
	SYNTAX	   Integer32
	MAX-ACCESS read-only
	STATUS	   obsolete
	DESCRIPTION
		"Association ID
		Device Allocation: AP"
	::= { cambiumAPConnectedSTAListEntry 2 }

connectedSTAListChannel OBJECT-TYPE
	SYNTAX	   Integer32
	MAX-ACCESS read-only
	STATUS	   obsolete
	DESCRIPTION
		"Connected SM Channel
		Device Allocation: AP"
	::= { cambiumAPConnectedSTAListEntry 3 }

connectedSTAListULRSSI OBJECT-TYPE
	SYNTAX	   Integer32
	MAX-ACCESS read-only
	STATUS	   obsolete
	DESCRIPTION
		"UL RSSI per SM
		Device Allocation: AP"
	::= { cambiumAPConnectedSTAListEntry 4 }

connectedSTAListDLRSSI OBJECT-TYPE
	SYNTAX	   Integer32
	MAX-ACCESS read-only
	STATUS	   obsolete
	DESCRIPTION
		"DL RSSI per SM
		Device Allocation: AP"
	::= { cambiumAPConnectedSTAListEntry 5 }

connectedSTAListULCINR OBJECT-TYPE
	SYNTAX	   Integer32
	MAX-ACCESS read-only
	STATUS	   obsolete
	DESCRIPTION
		"UL CINR per SM
		Device Allocation: AP"
	::= { cambiumAPConnectedSTAListEntry 6 }

connectedSTAListDLCINR OBJECT-TYPE
	SYNTAX	   Integer32
	MAX-ACCESS read-only
	STATUS	   obsolete
	DESCRIPTION
		"DL CINR per SM
		Device Allocation: AP"
	::= { cambiumAPConnectedSTAListEntry 7 }

connectedSTAListULMCS OBJECT-TYPE
	SYNTAX	   Integer32 (1..15|20..29|30..39)
	MAX-ACCESS read-only
	STATUS	   obsolete
	DESCRIPTION
		"UL MCS Mode per SM:
			1 for MCS1,
			2 for MCS2,
			3 for MCS3,
			4 for MCS4,
			5 for MCS5,
			6 for MCS6,
			7 for MCS7,
			9 for MCS9,
			10 for MCS10,
			11 for MCS11,
			12 for MCS12,
			13 for MCS13,
			14 for MCS14,
			15 for MCS15,

			(Values in brackets represent IEEE 802.11ac rate codes)

			20 (0x80) for 'SS MCS 0 - BPSK 1/2',
			21 (0x81) for 'SS MCS 1 - QPSK 1/2',
			22 (0x82) for 'SS MCS 2 - QPSK 3/4',
			23 (0x83) for 'SS MCS 3 - 16-QAM 1/2',
			24 (0x84) for 'SS MCS 4 - 16-QAM 3/4',
			25 (0x85) for 'SS MCS 5 - 64-QAM 2/3',
			26 (0x86) for 'SS MCS 6 - 64-QAM 3/4',
			27 (0x87) for 'SS MCS 7 - 64-QAM 5/6',
			28 (0x88) for 'SS MCS 8 - 256-QAM 3/4',
			29 (0x89) for 'SS MCS 9 - 256-QAM 5/6',

			30 (0xd0) for 'DS MCS 0 - BPSK 1/2',
			31 (0xd1) for 'DS MCS 1 - QPSK 1/2',
			32 (0xd2) for 'DS MCS 2 - QPSK 3/4',
			33 (0xd3) for 'DS MCS 3 - 16-QAM 1/2',
			34 (0xd4) for 'DS MCS 4 - 16-QAM 3/4',
			35 (0xd5) for 'DS MCS 5 - 64-QAM 2/3',
			36 (0xd6) for 'DS MCS 6 - 64-QAM 3/4',
			37 (0xd7) for 'DS MCS 7 - 64-QAM 5/6',
			38 (0xd8) for 'DS MCS 8 - 256-QAM 3/4',
			39 (0xd9) for 'DS MCS 9 - 256-QAM 5/6'

		Device Allocation: AP"
	::= { cambiumAPConnectedSTAListEntry 8 }

connectedSTAListDLMCS OBJECT-TYPE
	SYNTAX	   Integer32 (1..15|20..29|30..39)
	MAX-ACCESS read-only
	STATUS	   obsolete
	DESCRIPTION
		"DL MCS Mode per SM:
			1 for MCS1,
			2 for MCS2,
			3 for MCS3,
			4 for MCS4,
			5 for MCS5,
			6 for MCS6,
			7 for MCS7,
			9 for MCS9,
			10 for MCS10,
			11 for MCS11,
			12 for MCS12,
			13 for MCS13,
			14 for MCS14,
			15 for MCS15,

			(Values in brackets represent IEEE 802.11ac rate codes)

			20 (0x80) for 'SS MCS 0 - BPSK 1/2',
			21 (0x81) for 'SS MCS 1 - QPSK 1/2',
			22 (0x82) for 'SS MCS 2 - QPSK 3/4',
			23 (0x83) for 'SS MCS 3 - 16-QAM 1/2',
			24 (0x84) for 'SS MCS 4 - 16-QAM 3/4',
			25 (0x85) for 'SS MCS 5 - 64-QAM 2/3',
			26 (0x86) for 'SS MCS 6 - 64-QAM 3/4',
			27 (0x87) for 'SS MCS 7 - 64-QAM 5/6',
			28 (0x88) for 'SS MCS 8 - 256-QAM 3/4',
			29 (0x89) for 'SS MCS 9 - 256-QAM 5/6',

			30 (0xd0) for 'DS MCS 0 - BPSK 1/2',
			31 (0xd1) for 'DS MCS 1 - QPSK 1/2',
			32 (0xd2) for 'DS MCS 2 - QPSK 3/4',
			33 (0xd3) for 'DS MCS 3 - 16-QAM 1/2',
			34 (0xd4) for 'DS MCS 4 - 16-QAM 3/4',
			35 (0xd5) for 'DS MCS 5 - 64-QAM 2/3',
			36 (0xd6) for 'DS MCS 6 - 64-QAM 3/4',
			37 (0xd7) for 'DS MCS 7 - 64-QAM 5/6',
			38 (0xd8) for 'DS MCS 8 - 256-QAM 3/4',
			39 (0xd9) for 'DS MCS 9 - 256-QAM 5/6'

		Device Allocation: AP"
	::= { cambiumAPConnectedSTAListEntry 9 }

connectedSTAListIP OBJECT-TYPE
	SYNTAX	   IpAddress
	MAX-ACCESS read-only
	STATUS	   obsolete
	DESCRIPTION
		"Connected SM WLAN IP Address
		Device Allocation: AP"
	::= { cambiumAPConnectedSTAListEntry 10 }

connectedSTAListMirSrc OBJECT-TYPE
	SYNTAX	   DisplayString
	MAX-ACCESS read-only
	STATUS	   obsolete
	DESCRIPTION
		"Connected SM MIR source: RADIUS server or profile ID
		Device Allocation: AP"
	::= { cambiumAPConnectedSTAListEntry 12 }

connectedSTAListMirULRate OBJECT-TYPE
	SYNTAX	   DisplayString
	MAX-ACCESS read-only
	STATUS	   obsolete
	DESCRIPTION
		"Connected SM MIR UL Rate
		Device Allocation: AP"
	::= { cambiumAPConnectedSTAListEntry 13 }

connectedSTAListMirDLRate OBJECT-TYPE
	SYNTAX	   DisplayString
	MAX-ACCESS read-only
	STATUS	   obsolete
	DESCRIPTION
		"Connected SM MIR DL Rate
		Device Allocation: AP"
	::= { cambiumAPConnectedSTAListEntry 14 }

cambiumSTADistanceKm OBJECT-TYPE
	SYNTAX	   DisplayString
	MAX-ACCESS read-only
	STATUS	   current
	DESCRIPTION
		"The distance between AP and SM in kilometers
		Device Allocation: SM"
	::= { cambiumRFStatus 12 }

cambiumSTADistanceMil OBJECT-TYPE
	SYNTAX	   DisplayString
	MAX-ACCESS read-only
	STATUS	   current
	DESCRIPTION
		"The distance between AP and SM in miles
		Device Allocation: SM"
	::= { cambiumRFStatus 13 }

cambiumPropagationDelay OBJECT-TYPE
	SYNTAX	   Integer32 (-2000..5000000)
	MAX-ACCESS read-only
	STATUS	   current
	DESCRIPTION
		"SM use the calculated propagation delay to adjust the UL starting time
		Device Allocation: SM"
	::= { cambiumRFStatus 14 }

cambiumSTAConnectedAPListTable OBJECT-TYPE
	SYNTAX	   SEQUENCE OF CambiumSTAConnectedAPListEntry
	MAX-ACCESS not-accessible
	STATUS	   obsolete
	DESCRIPTION
		"This table contains information relevant to the Connected Subscriber Modules:
			SSID - AP Name (SSID)
			BSSID - AP MAC Address
			Channel - Operating channgel number
			Frequency - AP Operating frequency
			Bandwitdth - AP Operating Bandwidth
			Rate - AP Operating Rate
			CINR - AP Signal to Noise Ratio
			RSSI - AP Received Signal Strength Indication
			Noise - AP Noise level
			INT - Beacon Interval
			NE_ST - Last Network Entry State
			NE_AGE - Time from last Network Entry event
			SCAN_AGE - Time from last AP scanning
			Remaining_SM  - Capacity on AP from beacon
			CAPS - IEEE80211 capability flags
			MeetNEAttemptCriteria - status for eachAP after scanning
		Device Allocation: SM"
	::= { cambiumRFStatus 15 }

cambiumSTAConnectedAPListEntry OBJECT-TYPE
	SYNTAX	   CambiumSTAConnectedAPListEntry
	MAX-ACCESS not-accessible
	STATUS	   obsolete
	DESCRIPTION
		"Wireless parameters mapping for particular station.
		Device Allocation: SM"
	INDEX	{ connectedAPListSSID }
	::= { cambiumSTAConnectedAPListTable 1 }

CambiumSTAConnectedAPListEntry ::= SEQUENCE {
	connectedAPListSSID			DisplayString,
	connectedAPListBSSID		DisplayString,
	connectedAPListChannel		Integer32,
	connectedAPListFrequency	Integer32,
	connectedAPListBandwidth	DisplayString,
	connectedAPListRate			DisplayString,
	connectedAPListCINR			Integer32,
	connectedAPListRSSI			Integer32,
	connectedAPListNoise		Integer32,
	connectedAPListINT			Integer32,
	connectedAPListNEState		Integer32,
	connectedAPListNEAge		DisplayString,
	connectedAPListScanAge		DisplayString,
	connectedAPListRemainingSTA	Integer32,
	connectedAPListCAPS			DisplayString,
	connectedAPAuthMethod		DisplayString,
	connectedAPListMeetNEAttemptCriteria	DisplayString
}

connectedAPListSSID OBJECT-TYPE
	SYNTAX	   DisplayString
	MAX-ACCESS read-only
	STATUS	   obsolete
	DESCRIPTION
		"AP Name (SSID)
		Device Allocation: SM"
	::= { cambiumSTAConnectedAPListEntry 1 }

connectedAPListBSSID OBJECT-TYPE
	SYNTAX	   DisplayString
	MAX-ACCESS read-only
	STATUS	   obsolete
	DESCRIPTION
		"AP MAC Address
		Device Allocation: SM"
	::= { cambiumSTAConnectedAPListEntry 2 }

connectedAPListChannel OBJECT-TYPE
	SYNTAX	   Integer32
	MAX-ACCESS read-only
	STATUS	   obsolete
	DESCRIPTION
		"Operating channgel number
		Device Allocation: SM"
	::= { cambiumSTAConnectedAPListEntry 3 }

connectedAPListFrequency OBJECT-TYPE
	SYNTAX	   Integer32
	MAX-ACCESS read-only
	STATUS	   obsolete
	DESCRIPTION
		"AP Operating frequency
		Device Allocation: SM"
	::= { cambiumSTAConnectedAPListEntry 4 }

connectedAPListBandwidth OBJECT-TYPE
	SYNTAX	   DisplayString
	MAX-ACCESS read-only
	STATUS	   obsolete
	DESCRIPTION
		"AP Operating Bandwidth
		Device Allocation: SM"
	::= { cambiumSTAConnectedAPListEntry 5 }

connectedAPListRate OBJECT-TYPE
	SYNTAX	   DisplayString
	MAX-ACCESS read-only
	STATUS	   obsolete
	DESCRIPTION
		"AP Operating Rate
		Device Allocation: SM"
	::= { cambiumSTAConnectedAPListEntry 6 }

connectedAPListCINR OBJECT-TYPE
	SYNTAX	   Integer32
	MAX-ACCESS read-only
	STATUS	   obsolete
	DESCRIPTION
		"AP	 Carrier to Interference Noise Ratio
		Device Allocation: SM"
	::= { cambiumSTAConnectedAPListEntry 7 }

connectedAPListRSSI	 OBJECT-TYPE
	SYNTAX	   Integer32
	MAX-ACCESS read-only
	STATUS	   obsolete
	DESCRIPTION
		"AP Received Signal Strength Indication
		Device Allocation: SM"
	::= { cambiumSTAConnectedAPListEntry 8 }

connectedAPListNoise  OBJECT-TYPE
	SYNTAX	   Integer32
	MAX-ACCESS read-only
	STATUS	   obsolete
	DESCRIPTION
		"AP Noise level
		Device Allocation: SM"
	::= { cambiumSTAConnectedAPListEntry 9 }

connectedAPListINT	OBJECT-TYPE
	SYNTAX	   Integer32
	MAX-ACCESS read-only
	STATUS	   obsolete
	DESCRIPTION
		"Beacon Interval
		Device Allocation: SM"
	::= { cambiumSTAConnectedAPListEntry 10 }

connectedAPListNEState	OBJECT-TYPE
	SYNTAX	   Integer32
	MAX-ACCESS read-only
	STATUS	   obsolete
	DESCRIPTION
		"Last Network Entry State
		Device Allocation: SM"
	::= { cambiumSTAConnectedAPListEntry 11 }

connectedAPListNEAge OBJECT-TYPE
	SYNTAX	   DisplayString
	MAX-ACCESS read-only
	STATUS	   obsolete
	DESCRIPTION
		"Time from last Network Entry event
		Device Allocation: SM"
	::= { cambiumSTAConnectedAPListEntry 12 }

connectedAPListScanAge OBJECT-TYPE
	SYNTAX	   DisplayString
	MAX-ACCESS read-only
	STATUS	   obsolete
	DESCRIPTION
		"Time from last AP scanning
		Device Allocation: SM"
	::= { cambiumSTAConnectedAPListEntry 13 }

connectedAPListRemainingSTA	 OBJECT-TYPE
	SYNTAX	   Integer32
	MAX-ACCESS read-only
	STATUS	   obsolete
	DESCRIPTION
		"Remaining SM on AP
		Device Allocation: SM"
	::= { cambiumSTAConnectedAPListEntry 14 }

connectedAPListCAPS OBJECT-TYPE
	SYNTAX	   DisplayString
	MAX-ACCESS read-only
	STATUS	   obsolete
	DESCRIPTION
		"IEEE80211 capability flags
		Device Allocation: SM"
	::= { cambiumSTAConnectedAPListEntry 15 }

connectedAPAuthMethod OBJECT-TYPE
	SYNTAX	   DisplayString
	MAX-ACCESS read-only
	STATUS	   obsolete
	DESCRIPTION
		   "Authentication Method
		   Device Allocation: SM"
	::= { cambiumSTAConnectedAPListEntry 16 }

connectedAPListMeetNEAttemptCriteria OBJECT-TYPE
	SYNTAX	   DisplayString
	MAX-ACCESS read-only
	STATUS	   obsolete
	DESCRIPTION
		   "Status meet NE attempt criteria
		   Device Allocation: SM"
	::= { cambiumSTAConnectedAPListEntry 17 }

wirelessInterfaceConnectionState OBJECT-TYPE
	SYNTAX Integer32 (1|2|3)
	MAX-ACCESS read-only
	STATUS	   current
	DESCRIPTION
		"Connection State:
			1 - Scanning,
			2 - Connecting,
			3 - Connected
		Device Allocation: SM"
	::= { cambiumRFStatus 16 }

cambiumSTAPriority OBJECT-TYPE
	SYNTAX	   Integer32 (0|1|2)
	MAX-ACCESS read-only
	STATUS	   current
	DESCRIPTION
		"SM priority value:
			0 - Normal,
			1 - High,
			2 - Low
		Device Allocation: SM"
	::= { cambiumRFStatus 17 }

cambiumSTADLSNR OBJECT-TYPE
	SYNTAX	   Integer32
	MAX-ACCESS read-only
	STATUS	   current
	DESCRIPTION
		"SM SNR in dBm
		Device Allocation: SM"
	::= { cambiumRFStatus 18 }

cambiumConnectedAPMACAddress OBJECT-TYPE
	SYNTAX	   DisplayString (SIZE(0|11..17))
	MAX-ACCESS read-only
	STATUS	   current
	DESCRIPTION
		"Connected AP MAC Address
		Device Allocation: SM"
	::= { cambiumRFStatus 19 }

cambiumSTAConnectedAPTable OBJECT-TYPE
	SYNTAX	   SEQUENCE OF CambiumSTAConnectedAPEntry
	MAX-ACCESS not-accessible
	STATUS	   current
	DESCRIPTION
		"This table contains information relevant to the Connected Subscriber Modules:
			SSID - AP Name (SSID)
			BSSID - AP MAC Address
			Channel - Operating channgel number
			Frequency - AP Operating frequency
			Bandwitdth - AP Operating Bandwidth
			Rate - AP Operating Rate
			SNR - AP Signal to Noise Ratio
			RSSI - AP Received Signal Strength Indication
			Noise - AP Noise level
			INT - Beacon Interval
			NE_ST - Last Network Entry State
			NE_AGE - Time from last Network Entry event
			SCAN_AGE - Time from last AP scanning
			Remaining_SM  - Capacity on AP from beacon
			CAPS - IEEE80211 capability flags
			MeetNEAttemptCriteria - status for eachAP after scanning
		Device Allocation: SM"
	::= { cambiumRFStatus 20 }

cambiumSTAConnectedAPEntry OBJECT-TYPE
	SYNTAX	   CambiumSTAConnectedAPEntry
	MAX-ACCESS not-accessible
	STATUS	   current
	DESCRIPTION
		"Wireless parameters mapping for particular station.
		Device Allocation: SM"
	INDEX	{ connectedAPListSSID }
	::= { cambiumSTAConnectedAPTable 1 }

CambiumSTAConnectedAPEntry ::= SEQUENCE {
	connectedAPSSID				DisplayString,
	connectedAPBSSID			DisplayString,
	connectedAPChannel			Integer32,
	connectedAPFrequency		Integer32,
	connectedAPBandwidth		DisplayString,
	connectedAPRate				DisplayString,
	connectedAPSNR				Integer32,
	connectedAPRSSI				Integer32,
	connectedAPNoise			Integer32,
	connectedAPINT				Integer32,
	connectedAPNEState			Integer32,
	connectedAPNEAge			DisplayString,
	connectedAPScanAge			DisplayString,
	connectedAPRemainingSTA		Integer32,
	connectedAPCAPS				DisplayString,
	connectedAPAuthenticationMethod		DisplayString,
	connectedAPMeetNEAttemptCriteria	DisplayString,
	connectedAPIsViaInterface		Integer32,
	connectedAPDriverMode			Integer32
}

connectedAPSSID OBJECT-TYPE
	SYNTAX	   DisplayString
	MAX-ACCESS read-only
	STATUS	   current
	DESCRIPTION
		"AP Name (SSID)
		Device Allocation: SM"
	::= { cambiumSTAConnectedAPEntry 1 }

connectedAPBSSID OBJECT-TYPE
	SYNTAX	   DisplayString
	MAX-ACCESS read-only
	STATUS	   current
	DESCRIPTION
		"AP MAC Address
		Device Allocation: SM"
	::= { cambiumSTAConnectedAPEntry 2 }

connectedAPChannel OBJECT-TYPE
	SYNTAX	   Integer32
	MAX-ACCESS read-only
	STATUS	   current
	DESCRIPTION
		"Operating channgel number
		Device Allocation: SM"
	::= { cambiumSTAConnectedAPEntry 3 }

connectedAPFrequency OBJECT-TYPE
	SYNTAX	   Integer32
	MAX-ACCESS read-only
	STATUS	   current
	DESCRIPTION
		"AP Operating frequency
		Device Allocation: SM"
	::= { cambiumSTAConnectedAPEntry 4 }

connectedAPBandwidth OBJECT-TYPE
	SYNTAX	   DisplayString
	MAX-ACCESS read-only
	STATUS	   current
	DESCRIPTION
		"AP Operating Bandwidth
		Device Allocation: SM"
	::= { cambiumSTAConnectedAPEntry 5 }

connectedAPRate OBJECT-TYPE
	SYNTAX	   DisplayString
	MAX-ACCESS read-only
	STATUS	   current
	DESCRIPTION
		"AP Operating Rate
		Device Allocation: SM"
	::= { cambiumSTAConnectedAPEntry 6 }

connectedAPSNR OBJECT-TYPE
	SYNTAX	   Integer32
	MAX-ACCESS read-only
	STATUS	   current
	DESCRIPTION
		"AP Signal to Noise Ratio
		Device Allocation: SM"
	::= { cambiumSTAConnectedAPEntry 7 }

connectedAPRSSI	 OBJECT-TYPE
	SYNTAX	   Integer32
	MAX-ACCESS read-only
	STATUS	   current
	DESCRIPTION
		"AP Received Signal Strength Indication
		Device Allocation: SM"
	::= { cambiumSTAConnectedAPEntry 8 }

connectedAPNoise  OBJECT-TYPE
	SYNTAX	   Integer32
	MAX-ACCESS read-only
	STATUS	   current
	DESCRIPTION
		"AP Noise level
		Device Allocation: SM"
	::= { cambiumSTAConnectedAPEntry 9 }

connectedAPINT	OBJECT-TYPE
	SYNTAX	   Integer32
	MAX-ACCESS read-only
	STATUS	   current
	DESCRIPTION
		"Beacon Interval
		Device Allocation: SM"
	::= { cambiumSTAConnectedAPEntry 10 }

connectedAPNEState	OBJECT-TYPE
	SYNTAX	   Integer32
	MAX-ACCESS read-only
	STATUS	   current
	DESCRIPTION
		"Last Network Entry State
		Device Allocation: SM"
	::= { cambiumSTAConnectedAPEntry 11 }

connectedAPNEAge OBJECT-TYPE
	SYNTAX	   DisplayString
	MAX-ACCESS read-only
	STATUS	   current
	DESCRIPTION
		"Time from last Network Entry event
		Device Allocation: SM"
	::= { cambiumSTAConnectedAPEntry 12 }

connectedAPScanAge OBJECT-TYPE
	SYNTAX	   DisplayString
	MAX-ACCESS read-only
	STATUS	   current
	DESCRIPTION
		"Time from last AP scanning
		Device Allocation: SM"
	::= { cambiumSTAConnectedAPEntry 13 }

connectedAPRemainingSTA	 OBJECT-TYPE
	SYNTAX	   Integer32
	MAX-ACCESS read-only
	STATUS	   current
	DESCRIPTION
		"Remaining SM on AP
		Device Allocation: SM"
	::= { cambiumSTAConnectedAPEntry 14 }

connectedAPCAPS OBJECT-TYPE
	SYNTAX	   DisplayString
	MAX-ACCESS read-only
	STATUS	   current
	DESCRIPTION
		"IEEE80211 capability flags
		Device Allocation: SM"
	::= { cambiumSTAConnectedAPEntry 15 }

connectedAPAuthenticationMethod OBJECT-TYPE
	SYNTAX	   DisplayString
	MAX-ACCESS read-only
	STATUS	   current
	DESCRIPTION
		   "Authentication Method
		   Device Allocation: SM"
	::= { cambiumSTAConnectedAPEntry 16 }

connectedAPMeetNEAttemptCriteria OBJECT-TYPE
	SYNTAX	   DisplayString
	MAX-ACCESS read-only
	STATUS	   current
	DESCRIPTION
		   "Status meet NE attempt criteria
		   Device Allocation: SM"
	::= { cambiumSTAConnectedAPEntry 17 }

connectedAPIsViaInterface OBJECT-TYPE
	SYNTAX	   Integer32
	MAX-ACCESS read-only
	STATUS	   current
	DESCRIPTION
		"Wireless interface number AP is visible via (starting from 0).
		Device Allocation: SM"
	::= { cambiumSTAConnectedAPEntry 18 }

connectedAPDriverMode OBJECT-TYPE
	SYNTAX	   Integer32
	MAX-ACCESS read-only
	STATUS	   current
	DESCRIPTION
		"Driver Mode"
	::= { cambiumSTAConnectedAPEntry 19 }

staTxCapacity OBJECT-TYPE
	SYNTAX	   Integer32 (0..100)
	MAX-ACCESS read-only
	STATUS	   current
	DESCRIPTION
		"TX Capacity for SM
		Device Allocation: SM"
	::= { cambiumRFStatus 21 }

staTxQuality OBJECT-TYPE
	SYNTAX	   Integer32 (0..100)
	MAX-ACCESS read-only
	STATUS	   current
	DESCRIPTION
		"TX Quality for SM
		Device Allocation: SM"
	::= { cambiumRFStatus 22 }

cambiumePMPElevateConnected OBJECT-TYPE
	SYNTAX	   Integer32 (1..128)
	MAX-ACCESS read-only
	STATUS	   current
	DESCRIPTION
		"Number of ePMP Elevate HW is connected to ePMP AP
		Device Allocation: AP"
	::= { cambiumRFStatus 23 }

cambiumRSSICh0 OBJECT-TYPE
	SYNTAX	   Integer32
	MAX-ACCESS read-only
	STATUS	   current
	DESCRIPTION
		"Device RSSI at chain 0 in dBm
		Device Allocation: AP (PTP mode), SM"
	::= { cambiumRFStatus 24 }

cambiumRSSICh1 OBJECT-TYPE
	SYNTAX	   Integer32
	MAX-ACCESS read-only
	STATUS	   current
	DESCRIPTION
		"Device RSSI at chain 1 in dBm
		Device Allocation: AP (PTP mode), SM"
	::= { cambiumRFStatus 25 }

acsState OBJECT-TYPE
	SYNTAX	   Integer32 (0..3)
	MAX-ACCESS read-only
	STATUS	   current
	DESCRIPTION
		"Indicates the state of the Automatic Channel Selection (ACS) feature:
		 0 - Disabled,
		 1 - Enabled,
		 2 - Running,
		 3 - Aborting
		Device Allocation: AP"
	::= { cambiumAcsStatus 1 }

cambiumEffectiveMcastGroupLimit OBJECT-TYPE
	SYNTAX	   Integer32 (0..10)
	MAX-ACCESS read-only
	STATUS	   current
	DESCRIPTION
		"Disaplays the Effective Multicast Group Limit number:
		 0 - 10 Groups
		Device Allocation: SM"
	::= { cambiumMcastStatus 1 }

cambiumSubscribedMcastGroupNum OBJECT-TYPE
	SYNTAX	   Integer32 (0..5)
	MAX-ACCESS read-only
	STATUS	   current
	DESCRIPTION
		"Disaplays the number of subscribed Multicast Groups:
		 0 - 5 Groups
		Device Allocation: SM"
	::= { cambiumMcastStatus 2 }

cambiumAPMcastTotalGroupCount OBJECT-TYPE
	SYNTAX	   Integer32 (0..512)
	MAX-ACCESS read-only
	STATUS	   current
	DESCRIPTION
		"Disaplays the count of subscribed Multicast Groups:
		 0 - 512 Groups
		Device Allocation: AP"
	::= { cambiumMcastStatus 3 }

cambiumMcastHandlingStatus OBJECT-TYPE
	SYNTAX	   Integer32 (0|3)
	MAX-ACCESS read-only
	STATUS	   current
	DESCRIPTION
		"Disaplays the status of the Multicast features:
			0 - Fixed MCS
			3 - Multicast to Unicast
		Device Allocation: AP"
	::= { cambiumMcastStatus 4 }

cambiumSubscribedMcastGroupTable OBJECT-TYPE
	SYNTAX	   SEQUENCE OF CambiumSubscribedMcastGroupEntry
	MAX-ACCESS not-accessible
	STATUS	   current
	DESCRIPTION
		"This table contains Registered Multicast Group information:
			Multicast Group IP
		Device Allocation: SM"
	::= { cambiumMcastStatus 10 }

cambiumSubscribedMcastGroupEntry OBJECT-TYPE
	SYNTAX	   CambiumSubscribedMcastGroupEntry
	MAX-ACCESS not-accessible
	STATUS	   current
	DESCRIPTION
		"Multicast group information for particular subscription
		Device Allocation: SM"
	INDEX	{ cambiumSubscribedMcastGroupNum }
	::= { cambiumSubscribedMcastGroupTable 1 }

CambiumSubscribedMcastGroupEntry ::= SEQUENCE {
	cambiumRegisteredMcastGroupIP			 IpAddress
}

cambiumRegisteredMcastGroupIP OBJECT-TYPE
	SYNTAX	   IpAddress
	MAX-ACCESS read-only
	STATUS	   current
	DESCRIPTION
		"Registered Multicast Group IP
		Device Allocation: SM"
	::= { cambiumSubscribedMcastGroupEntry 1 }

dhcpServerStartIP  OBJECT-TYPE
	SYNTAX	   IpAddress
	MAX-ACCESS read-write
	STATUS	   current
	DESCRIPTION
		"Dhcp server start address
		Device Allocation: STA"
	::= { cambiumDhcpStatus 1 }

dhcpServerEndIP	 OBJECT-TYPE
	SYNTAX	   IpAddress
	MAX-ACCESS read-write
	STATUS	   current
	DESCRIPTION
		"Dhcp server end address
		Device Allocation: STA"
	::= { cambiumDhcpStatus 2 }

dhcpServerGatewayIP	 OBJECT-TYPE
	SYNTAX	   IpAddress
	MAX-ACCESS read-write
	STATUS	   current
	DESCRIPTION
		"DHCP Gateway IP Address
		Device Allocation: STA"
	::= { cambiumDhcpStatus 3 }

dhcpServerDNSIP	 OBJECT-TYPE
	SYNTAX	   IpAddress
	MAX-ACCESS read-write
	STATUS	   current
	DESCRIPTION
		"DHCP server DNS IP Address
		Device Allocation: STA"
	::= { cambiumDhcpStatus 4 }

dhcpServerStaticHostTable  OBJECT-TYPE
	SYNTAX SEQUENCE OF DhcpServerStaticHostEntry
	MAX-ACCESS not-accessible
	STATUS	   current
	DESCRIPTION
		"Table for DHCP static MAC to IP"
	::= { cambiumDhcpStatus 5 }

cambLicenseVersion OBJECT-TYPE
	SYNTAX	   DisplayString (SIZE(0|1))
	MAX-ACCESS read-only
	STATUS	   current
	DESCRIPTION
		"Device Operational Lincense Version
		Device Allocation: AP, SM"
	::= { cambiumLicenseInfo 1 }

cambLicenseSMcntUnlock OBJECT-TYPE
	SYNTAX	   DisplayString (SIZE(0|1))
	MAX-ACCESS read-only
	STATUS	   current
	DESCRIPTION
		"Full Capacity AP feature unlock, based on information from
		 Operational Lincense
		Device Allocation: AP, SM"
	::= { cambiumLicenseInfo 2 }

cambLicenseMACaddr OBJECT-TYPE
	SYNTAX	   DisplayString (SIZE(0|17))
	MAX-ACCESS read-only
	STATUS	   current
	DESCRIPTION
		"Device Operational Lincense MAC address
		Device Allocation: AP, SM"
	::= { cambiumLicenseInfo 3 }

cambLicenseCountry OBJECT-TYPE
	SYNTAX	   DisplayString (SIZE(0|1..2))
	MAX-ACCESS read-only
	STATUS	   current
	DESCRIPTION
		"Country Code for ETSI locked device, based on information from
		 Operational Lincense
		Device Allocation: AP, SM"
	::= { cambiumLicenseInfo 4 }

cambLicenseStatus OBJECT-TYPE
	SYNTAX	   Integer32 (0..4)
	MAX-ACCESS read-only
	STATUS	   current
	DESCRIPTION
		"Device Operational Lincense Status:
		 0 - Unknown
		 1 - License Valid
		 2 - Validation procedure was not provided
		 3 - Validation Fail
		 4 - License not valid for current device
		Device Allocation: AP, SM"
	::= { cambiumLicenseInfo 5 }

cambLicenseDPIUnlockQoS OBJECT-TYPE
	SYNTAX     Integer32 (0..1)
	MAX-ACCESS read-only
	STATUS     current
	DESCRIPTION
		"Smart QoS feature state, based on information from Operational License
		 0 - Locked
		 1 - Unlocked
		Device Allocation: AP, SM"
	::= { cambiumLicenseInfo 6 }

dhcpServerStaticHostEntry OBJECT-TYPE
	SYNTAX	   DhcpServerStaticHostEntry
	MAX-ACCESS not-accessible
	STATUS	   current
	DESCRIPTION
		"DHCP Hosts Table Entry
		Device Allocation: STA"
	INDEX	{ dhcpStaticIndex }
	::= { dhcpServerStaticHostTable 1 }

DhcpServerStaticHostEntry ::= SEQUENCE {
	dhcpStaticIndex
		Integer32,
	dhcpStaticMAC
		DisplayString,
	dhcpStaticIP
		IpAddress
}

dhcpStaticIndex	 OBJECT-TYPE
	SYNTAX	   Integer32 (0..65535)
	MAX-ACCESS read-only
	STATUS	   current
	DESCRIPTION
		"DHCP Static Table Index"
	::= { dhcpServerStaticHostEntry 1 }

dhcpStaticMAC  OBJECT-TYPE
	SYNTAX	   DisplayString (SIZE(0|17))
	MAX-ACCESS read-only
	STATUS	   current
	DESCRIPTION
		"DHCP Static MAC"
	::= { dhcpServerStaticHostEntry 2 }

dhcpStaticIP  OBJECT-TYPE
	SYNTAX	   IpAddress
	MAX-ACCESS read-only
	STATUS	   current
	DESCRIPTION
		"DHCP Static IP"
	::= { dhcpServerStaticHostEntry 3 }

dhcpServerLeaseTable  OBJECT-TYPE
	SYNTAX SEQUENCE OF DhcpServerLeaseEntry
	MAX-ACCESS not-accessible
	STATUS	   current
	DESCRIPTION
		"DHCP Assigned IP Address Table"
	::= { cambiumDhcpStatus 6 }

networkRadiusVSAmgmtVLANVID  OBJECT-TYPE
	SYNTAX	   Integer32 (0|1..4095)
	MAX-ACCESS read-only
	STATUS	   current
	DESCRIPTION
		"VSA Management VLAN ID"
	::= { cambiumRadiusVSAStatus 1 }

networkRadiusVSAmgmtVLANVP  OBJECT-TYPE
	SYNTAX	   Integer32 (0|1..7)
	MAX-ACCESS read-only
	STATUS	   current
	DESCRIPTION
		"VSA Management VLAN VP"
	::= { cambiumRadiusVSAStatus 2 }

networkRadiusVSAdataVLANVID  OBJECT-TYPE
	SYNTAX	   Integer32 (0|1..4095)
	MAX-ACCESS read-only
	STATUS	   current
	DESCRIPTION
		"VSA Data VLAN ID"
	::= { cambiumRadiusVSAStatus 3 }

networkRadiusVSAdataVLANVP  OBJECT-TYPE
	SYNTAX	   Integer32 (0|1..7)
	MAX-ACCESS read-only
	STATUS	   current
	DESCRIPTION
		"VSA Data VLAN VP"
	::= { cambiumRadiusVSAStatus 4 }

networkRadiusVSAmgmtIFVID  OBJECT-TYPE
	SYNTAX	   Integer32 (0|1..4095)
	MAX-ACCESS read-only
	STATUS	   current
	DESCRIPTION
		"VSA Separate Management Interface VLAN ID"
	::= { cambiumRadiusVSAStatus 5 }

networkRadiusVSAmgmtIFVP  OBJECT-TYPE
	SYNTAX	   Integer32 (0|1..7)
	MAX-ACCESS read-only
	STATUS	   current
	DESCRIPTION
		"VSA Separate Management Interface VLAN VP"
	::= { cambiumRadiusVSAStatus 6 }

networkRadiusVSAmcastVLANVID  OBJECT-TYPE
	SYNTAX	   Integer32 (0|1..4095)
	MAX-ACCESS read-only
	STATUS	   current
	DESCRIPTION
		"VSA Multicast VLAN ID"
	::= { cambiumRadiusVSAStatus 7 }

networkRadiusVSAGUIauthType OBJECT-TYPE
	SYNTAX	   Integer32 (0|1|2)
	MAX-ACCESS read-only
	STATUS	   current
	DESCRIPTION
		"GUI User Authentication Type received from AP
			0 - Device Local Only
			1 - Remote RADIUS Server Only
			2 - Remote RADIUS Server and Fallback to Local
		Device Allocation: SM"
	::= { cambiumRadiusVSAStatus 8 }

networkRadiusVSAmembershipVLANTable OBJECT-TYPE
	SYNTAX SEQUENCE OF NetworkRadiusVSAmembershipVLANEntry
	MAX-ACCESS not-accessible
	STATUS     current
	DESCRIPTION
		"VSA Membership VLAN Table"
	INDEX   { networkRadiusVSAmembershipVLANIndex }
	::= { cambiumRadiusVSAStatus 10 }

networkRadiusVSAmembershipVLANEntry OBJECT-TYPE
	SYNTAX	   NetworkRadiusVSAmembershipVLANEntry
	MAX-ACCESS not-accessible
	STATUS	   current
	DESCRIPTION
		"VSA Membership VLAN Table Rule Entry"
	INDEX	{ networkRadiusVSAmembershipVLANIndex }
	::= { networkRadiusVSAmembershipVLANTable 1 }

NetworkRadiusVSAmembershipVLANEntry ::= SEQUENCE {
	networkRadiusVSAmembershipVLANIndex
		Integer32,
	networkRadiusVSAmembershipVLANVIDBegin
		Integer32,
	networkRadiusVSAmembershipVLANVIDEnd
		Integer32
}

networkRadiusVSAmembershipVLANIndex  OBJECT-TYPE
	SYNTAX	  Integer32 (0..16)
	MAX-ACCESS read-only
	STATUS	   current
	DESCRIPTION
		"VSA Membership VLAN Table Entry Index"
	::= { networkRadiusVSAmembershipVLANEntry 1 }

networkRadiusVSAmembershipVLANVIDBegin  OBJECT-TYPE
	SYNTAX	   Integer32 (0|1..4095)
	MAX-ACCESS read-only
	STATUS	   current
	DESCRIPTION
		"VSA Membership VLAN Table Entry VLAN ID Begin"
	::= { networkRadiusVSAmembershipVLANEntry 2 }

networkRadiusVSAmembershipVLANVIDEnd  OBJECT-TYPE
	SYNTAX	   Integer32 (0|1..4095)
	MAX-ACCESS read-only
	STATUS	   current
	DESCRIPTION
		"VSA Membership VLAN Table Entry VLAN ID End"
	::= { networkRadiusVSAmembershipVLANEntry 3 }

networkRadiusVSAmappingVLANTable OBJECT-TYPE
	SYNTAX SEQUENCE OF NetworkRadiusVSAmappingVLANEntry
	MAX-ACCESS not-accessible
	STATUS     current
	DESCRIPTION
		"VSA Mapping VLAN Table Rule Entry"
	INDEX   { networkRadiusVSAmappingVLANIndex }
	::= { cambiumRadiusVSAStatus 20 }

networkRadiusVSAmappingVLANEntry  OBJECT-TYPE
	SYNTAX	   NetworkRadiusVSAmappingVLANEntry
	MAX-ACCESS not-accessible
	STATUS	   current
	DESCRIPTION
		"VSA Mapping VLAN Table Rule Entry"
	INDEX	{ networkRadiusVSAmappingVLANIndex }
	::= { networkRadiusVSAmappingVLANTable 1 }

NetworkRadiusVSAmappingVLANEntry ::= SEQUENCE {
	networkRadiusVSAmappingVLANIndex
		Integer32,
	networkRadiusVSAmappingVLANCVLAN
		Integer32,
	networkRadiusVSAmappingVLANSVLAN
		Integer32
}

networkRadiusVSAmappingVLANIndex  OBJECT-TYPE
	SYNTAX	  Integer32 (0..16)
	MAX-ACCESS read-only
	STATUS	   current
	DESCRIPTION
		"VSA Mapping VLAN Table Entry Index"
	::= { networkRadiusVSAmappingVLANEntry 1 }

networkRadiusVSAmappingVLANCVLAN  OBJECT-TYPE
	SYNTAX	   Integer32 (0|1..4095)
	MAX-ACCESS read-only
	STATUS	   current
	DESCRIPTION
		"VSA Mapping VLAN Table C-VLAN ID"
	::= { networkRadiusVSAmappingVLANEntry 2 }

networkRadiusVSAmappingVLANSVLAN  OBJECT-TYPE
	SYNTAX	   Integer32 (0|1..4095)
	MAX-ACCESS read-only
	STATUS	   current
	DESCRIPTION
		"VSA Mapping VLAN Table S-VLAN ID"
	::= { networkRadiusVSAmappingVLANEntry 3 }

dhcpServerLeaseEntry OBJECT-TYPE
	SYNTAX	   DhcpServerLeaseEntry
	MAX-ACCESS not-accessible
	STATUS	   current
	DESCRIPTION
		"DHCP Assigned IP Address Entry
		Device Allocation: STA"
	INDEX	{ dhcpLeaseIndex }
	::= { dhcpServerLeaseTable 1 }

DhcpServerLeaseEntry ::= SEQUENCE {
	dhcpLeaseIndex
		Integer32,
	dhcpLeaseMAC
		DisplayString,
	dhcpLeaseIP
		IpAddress,
	dhcpLeaseDevName
		DisplayString
}

dhcpLeaseIndex	OBJECT-TYPE
	SYNTAX	   Integer32 (0..65535)
	MAX-ACCESS read-only
	STATUS	   current
	DESCRIPTION
		"DHCP lease table index"
	::= { dhcpServerLeaseEntry 1 }

dhcpLeaseMAC  OBJECT-TYPE
	SYNTAX	   DisplayString (SIZE(0|17))
	MAX-ACCESS read-only
	STATUS	   current
	DESCRIPTION
		"DHCP Assigned MAC Address"
	::= { dhcpServerLeaseEntry 2 }

dhcpLeaseIP	 OBJECT-TYPE
	SYNTAX	   IpAddress
	MAX-ACCESS read-only
	STATUS	   current
	DESCRIPTION
		"DHCP Assigned IP Address"
	::= { dhcpServerLeaseEntry 3 }

dhcpLeaseDevName  OBJECT-TYPE
	SYNTAX	   DisplayString
	MAX-ACCESS read-only
	STATUS	   current
	DESCRIPTION
		"DHCP Assigned Device Name"
	::= { dhcpServerLeaseEntry 4 }

cambiumAPConnectedSTATable OBJECT-TYPE
	SYNTAX	   SEQUENCE OF CambiumAPConnectedSTAEntry
	MAX-ACCESS not-accessible
	STATUS	   current
	DESCRIPTION
		"This table contains information relevant to the Connected Subscriber Modules:
			Subscriber Module MAC Address,
			Subscriber Module AID,
			Subscriber Module Channel,
			UL RSSI per SM,
			DL RSSI per SM,
			UL SNR per SM,
			DL SNR per SM,
			UL MCS Mode per SM,
			DL MCS Mode per SM,
			Subscriber Module IP Address,
			SM Priority,
			MIR,
			MIR UL Rate,
			MIR DL Rate,
		Device Allocation: AP"
	::= { cambiumRFStatus 30 }

cambiumAPConnectedSTAEntry OBJECT-TYPE
	SYNTAX	   CambiumAPConnectedSTAEntry
	MAX-ACCESS not-accessible
	STATUS	   current
	DESCRIPTION
		"Wireless parameters mapping for particular station.
		Device Allocation: AP"
	INDEX	{ cambiumAPNumberOfConnectedSTA }
	::= { cambiumAPConnectedSTATable 1 }

CambiumAPConnectedSTAEntry ::= SEQUENCE {
	connectedSTAMAC			DisplayString,
	connectedSTAAID			Integer32,
	connectedSTAChannel		Integer32,
	connectedSTAULRSSI		Integer32,
	connectedSTADLRSSI		Integer32,
	connectedSTAULSNR		Integer32,
	connectedSTADLSNR		Integer32,
	connectedSTAULMCS		Integer32,
	connectedSTADLMCS		Integer32,
	connectedSTAIP			IpAddress,
	connectedSTAPriority		DisplayString,
	connectedSTAMirSrc		DisplayString,
	connectedSTAMirULRate		DisplayString,
	connectedSTAMirDLRate		DisplayString,
	connectedSTAClickTHWAddr	DisplayString,
	connectedSTAClickTWebPort	Integer32,
	connectedSTAClickTWebSec	Integer32,
	connectedSTAClickTHostName	DisplayString,
	connectedSTATXCapacity		Integer32,
	connectedSTATXQuality		Integer32,
	connectedSTAMcastTotalGroups	Integer32,
	connectedSTAMcastGRP0		IpAddress,
	connectedSTAMcastGRP1		IpAddress,
	connectedSTAMcastGRP2		IpAddress,
	connectedSTAMcastGRP3		IpAddress,
	connectedSTAMcastGRP4		IpAddress,
	connectedSTASessionTime		DisplayString,
	connectedSTADLRateMbps		DisplayString,
	connectedSTADistance		Integer32,
	connectedSTAVerticalAngle	DisplayString,
	connectedSTAHorizontalAngle	DisplayString,
	connectedSTAIsForcedAngle	Integer32,
	connectedSTASKU			Integer32,
	connectedSTALinktestForceAllow	Integer32,
	connectedSTAIPv6		Ipv6Address,
	connectedSTAIsViaInterface	Integer32,
	connectedSTAMUMIMOGain		Integer32,
	connectedSTAModelName		DisplayString,
	connectedSTAMUMIMOAzMetric	Integer32,
	connectedSTAMUMIMOQuality	Integer32,
	connectedSTAMUMIMORate		Integer32,
	connectedSTAMUMIMOPairs		Integer32,
	connectedSTASoftwareVersion	DisplayString
}

connectedSTAMAC OBJECT-TYPE
	SYNTAX	   DisplayString (SIZE(0|11..17))
	MAX-ACCESS read-only
	STATUS	   current
	DESCRIPTION
		"Connected SM WLAN MAC Address
		Device Allocation: AP"
	::= { cambiumAPConnectedSTAEntry 1 }

connectedSTAAID OBJECT-TYPE
	SYNTAX	   Integer32
	MAX-ACCESS read-only
	STATUS	   current
	DESCRIPTION
		"Association ID
		Device Allocation: AP"
	::= { cambiumAPConnectedSTAEntry 2 }

connectedSTAChannel OBJECT-TYPE
	SYNTAX	   Integer32
	MAX-ACCESS read-only
	STATUS	   current
	DESCRIPTION
		"Connected SM Channel
		Device Allocation: AP"
	::= { cambiumAPConnectedSTAEntry 3 }

connectedSTAULRSSI OBJECT-TYPE
	SYNTAX	   Integer32
	MAX-ACCESS read-only
	STATUS	   current
	DESCRIPTION
		"UL RSSI per SM
		Device Allocation: AP"
	::= { cambiumAPConnectedSTAEntry 4 }

connectedSTADLRSSI OBJECT-TYPE
	SYNTAX	   Integer32
	MAX-ACCESS read-only
	STATUS	   current
	DESCRIPTION
		"DL RSSI per SM
		Device Allocation: AP"
	::= { cambiumAPConnectedSTAEntry 5 }

connectedSTAULSNR OBJECT-TYPE
	SYNTAX	   Integer32
	MAX-ACCESS read-only
	STATUS	   current
	DESCRIPTION
		"UL SNR per SM
		Device Allocation: AP"
	::= { cambiumAPConnectedSTAEntry 6 }

connectedSTADLSNR OBJECT-TYPE
	SYNTAX	   Integer32
	MAX-ACCESS read-only
	STATUS	   current
	DESCRIPTION
		"DL SNR per SM
		Device Allocation: AP"
	::= { cambiumAPConnectedSTAEntry 7 }

connectedSTAULMCS OBJECT-TYPE
	SYNTAX	   Integer32
	MAX-ACCESS read-only
	STATUS	   current
	DESCRIPTION
		"UL MCS Mode per SM:
		This parameter represents Uplink MCS mode number for both 802.11n and 802.11ac standard devices.

		802.11n HW:

		1  for MCS1,
		2  for MCS2,
		3  for MCS3,
		4  for MCS4,
		5  for MCS5,
		6  for MCS6,
		7  for MCS7,
		9  for MCS9,
		10 for MCS10,
		11 for MCS11,
		12 for MCS12,
		13 for MCS13,
		14 for MCS14,
		15 for MCS15,

		802.11ac HW:

		0  for 'SS MCS 0 - BPSK 1/2',
		1  for 'SS MCS 1 - QPSK 1/2',
		2  for 'SS MCS 2 - QPSK 3/4',
		3  for 'SS MCS 3 - 16-QAM 1/2',
		4  for 'SS MCS 4 - 16-QAM 3/4',
		5  for 'SS MCS 5 - 64-QAM 2/3',
		6  for 'SS MCS 6 - 64-QAM 3/4',
		7  for 'SS MCS 7 - 64-QAM 5/6',
		8  for 'SS MCS 8 - 256-QAM 3/4',
		9  for 'SS MCS 9 - 256-QAM 5/6',

		10 for 'DS MCS 0 - BPSK 1/2',
		11 for 'DS MCS 1 - QPSK 1/2',
		12 for 'DS MCS 2 - QPSK 3/4',
		13 for 'DS MCS 3 - 16-QAM 1/2',
		14 for 'DS MCS 4 - 16-QAM 3/4',
		15 for 'DS MCS 5 - 64-QAM 2/3',
		16 for 'DS MCS 6 - 64-QAM 3/4',
		17 for 'DS MCS 7 - 64-QAM 5/6',
		18 for 'DS MCS 8 - 256-QAM 3/4',
		19 for 'DS MCS 9 - 256-QAM 5/6'

		Device Allocation: AP"
	::= { cambiumAPConnectedSTAEntry 8 }

connectedSTADLMCS OBJECT-TYPE
	SYNTAX	   Integer32
	MAX-ACCESS read-only
	STATUS	   current
	DESCRIPTION
		"DL MCS Mode per SM:
		This parameter represents Downlink MCS mode number for both 802.11n and 802.11ac standard devices.

		802.11n HW:

		1  for MCS1,
		2  for MCS2,
		3  for MCS3,
		4  for MCS4,
		5  for MCS5,
		6  for MCS6,
		7  for MCS7,
		9  for MCS9,
		10 for MCS10,
		11 for MCS11,
		12 for MCS12,
		13 for MCS13,
		14 for MCS14,
		15 for MCS15,

		802.11ac HW:

		0  for 'SS MCS 0 - BPSK 1/2',
		1  for 'SS MCS 1 - QPSK 1/2',
		2  for 'SS MCS 2 - QPSK 3/4',
		3  for 'SS MCS 3 - 16-QAM 1/2',
		4  for 'SS MCS 4 - 16-QAM 3/4',
		5  for 'SS MCS 5 - 64-QAM 2/3',
		6  for 'SS MCS 6 - 64-QAM 3/4',
		7  for 'SS MCS 7 - 64-QAM 5/6',
		8  for 'SS MCS 8 - 256-QAM 3/4',
		9  for 'SS MCS 9 - 256-QAM 5/6',

		10 for 'DS MCS 0 - BPSK 1/2',
		11 for 'DS MCS 1 - QPSK 1/2',
		12 for 'DS MCS 2 - QPSK 3/4',
		13 for 'DS MCS 3 - 16-QAM 1/2',
		14 for 'DS MCS 4 - 16-QAM 3/4',
		15 for 'DS MCS 5 - 64-QAM 2/3',
		16 for 'DS MCS 6 - 64-QAM 3/4',
		17 for 'DS MCS 7 - 64-QAM 5/6',
		18 for 'DS MCS 8 - 256-QAM 3/4',
		19 for 'DS MCS 9 - 256-QAM 5/6'

		Device Allocation: AP"
	::= { cambiumAPConnectedSTAEntry 9 }

connectedSTAIP OBJECT-TYPE
	SYNTAX	   IpAddress
	MAX-ACCESS read-only
	STATUS	   current
	DESCRIPTION
		"Connected SM WLAN IP Address
		Device Allocation: AP"
	::= { cambiumAPConnectedSTAEntry 10 }

connectedSTAPriority OBJECT-TYPE
	SYNTAX	   DisplayString
	MAX-ACCESS read-only
	STATUS	   current
	DESCRIPTION
		"Connected SM Priority
		Device Allocation: AP"
	::= { cambiumAPConnectedSTAEntry 11 }

connectedSTAMirSrc OBJECT-TYPE
	SYNTAX	   DisplayString
	MAX-ACCESS read-only
	STATUS	   current
	DESCRIPTION
		"Connected SM MIR source: RADIUS server or profile ID
		Device Allocation: AP"
	::= { cambiumAPConnectedSTAEntry 12 }

connectedSTAMirULRate OBJECT-TYPE
	SYNTAX	   DisplayString
	MAX-ACCESS read-only
	STATUS	   current
	DESCRIPTION
		"Connected SM MIR UL Rate
		Device Allocation: AP"
	::= { cambiumAPConnectedSTAEntry 13 }

connectedSTAMirDLRate OBJECT-TYPE
	SYNTAX	   DisplayString
	MAX-ACCESS read-only
	STATUS	   current
	DESCRIPTION
		"Connected SM MIR DL Rate
		Device Allocation: AP"
	::= { cambiumAPConnectedSTAEntry 14 }

connectedSTAClickTHWAddr OBJECT-TYPE
	SYNTAX	   DisplayString
	MAX-ACCESS read-only
	STATUS	   current
	DESCRIPTION
		"Connected SM BR or NAT HW addr
		Device Allocation: AP"
	::= { cambiumAPConnectedSTAEntry 15 }

connectedSTAClickTWebPort OBJECT-TYPE
	SYNTAX	   Integer32
	MAX-ACCESS read-only
	STATUS	   current
	DESCRIPTION
		"Connected SM WEB port
		Device Allocation: AP"
	::= { cambiumAPConnectedSTAEntry 16 }

connectedSTAClickTWebSec OBJECT-TYPE
	SYNTAX	   Integer32
	MAX-ACCESS read-only
	STATUS	   current
	DESCRIPTION
		"Connected SM WEB security (HTTPS)
		Device Allocation: AP"
	::= { cambiumAPConnectedSTAEntry 17 }

connectedSTAClickTHostName OBJECT-TYPE
	SYNTAX	   DisplayString
	MAX-ACCESS read-only
	STATUS	   current
	DESCRIPTION
		"Connected SM Host Name
		Device Allocation: AP"
	::= { cambiumAPConnectedSTAEntry 18 }
connectedSTATXCapacity OBJECT-TYPE
	SYNTAX     Integer32 (0..100)
	MAX-ACCESS read-only
	STATUS     current
	DESCRIPTION
		"TX Capacity per SM
		Device Allocation: AP"
	::= { cambiumAPConnectedSTAEntry 19 }

connectedSTATXQuality OBJECT-TYPE
	SYNTAX     Integer32 (0..100)
	MAX-ACCESS read-only
	STATUS     current
	DESCRIPTION
		"TX Quality per SM
		Device Allocation: AP"
	::= { cambiumAPConnectedSTAEntry 20 }

connectedSTAMcastTotalGroups OBJECT-TYPE
	SYNTAX	   Integer32
	MAX-ACCESS read-only
	STATUS	   current
	DESCRIPTION
		"Connected SM Total multicast groups
		subscribed count
		Device Allocation: AP"
	::= { cambiumAPConnectedSTAEntry 21 }

connectedSTAMcastGRP0 OBJECT-TYPE
	SYNTAX	   IpAddress
	MAX-ACCESS read-only
	STATUS	   current
	DESCRIPTION
		"Connected SM subscribed multicast
		group 0
		Device Allocation: AP"
	::= { cambiumAPConnectedSTAEntry 22 }

connectedSTAMcastGRP1 OBJECT-TYPE
	SYNTAX	   IpAddress
	MAX-ACCESS read-only
	STATUS	   current
	DESCRIPTION
		"Connected SM subscribed multicast
		group 1
		Device Allocation: AP"
	::= { cambiumAPConnectedSTAEntry 23 }

connectedSTAMcastGRP2 OBJECT-TYPE
	SYNTAX	   IpAddress
	MAX-ACCESS read-only
	STATUS	   current
	DESCRIPTION
		"Connected SM subscribed multicast
		group 2
		Device Allocation: AP"
	::= { cambiumAPConnectedSTAEntry 24 }

connectedSTAMcastGRP3 OBJECT-TYPE
	SYNTAX	   IpAddress
	MAX-ACCESS read-only
	STATUS	   current
	DESCRIPTION
		"Connected SM subscribed multicast
		group 3
		Device Allocation: AP"
	::= { cambiumAPConnectedSTAEntry 25 }

connectedSTAMcastGRP4 OBJECT-TYPE
	SYNTAX	   IpAddress
	MAX-ACCESS read-only
	STATUS	   current
	DESCRIPTION
		"Connected SM subscribed multicast
		group 4
		Device Allocation: AP"
	::= { cambiumAPConnectedSTAEntry 26 }

connectedSTASessionTime OBJECT-TYPE
	SYNTAX	   DisplayString
	MAX-ACCESS read-only
	STATUS	   current
	DESCRIPTION
		"Connected SM time since allocation
		Device Allocation: AP"
	::= { cambiumAPConnectedSTAEntry 27 }

connectedSTADLRateMbps OBJECT-TYPE
	SYNTAX	   DisplayString
	MAX-ACCESS read-only
	STATUS	   current
	DESCRIPTION
		"Connected SM DL Rate in MBits/sec
		Device Allocation: AP"
	::= { cambiumAPConnectedSTAEntry 28 }

connectedSTADistance OBJECT-TYPE
	SYNTAX	   Integer32
	MAX-ACCESS read-only
	STATUS	   current
	DESCRIPTION
		"STA distnce to AP
		Device Allocation: AP"
	::= { cambiumAPConnectedSTAEntry 29 }

connectedSTAVerticalAngle OBJECT-TYPE
	SYNTAX	   DisplayString
	MAX-ACCESS read-only
	STATUS	   current
	DESCRIPTION
		"Connected SM vertical angle"
	::= { cambiumAPConnectedSTAEntry 30 }

connectedSTAHorizontalAngle OBJECT-TYPE
	SYNTAX	   DisplayString
	MAX-ACCESS read-only
	STATUS	   current
	DESCRIPTION
		"Connected SM horizontal angle"
	::= { cambiumAPConnectedSTAEntry 31 }

connectedSTAIsForcedAngle OBJECT-TYPE
	SYNTAX     Integer32 (0..3)
	MAX-ACCESS read-only
	STATUS     current
	DESCRIPTION
		"Shows that antenna is forced by user.
		 Bit 0 - polarization H, Bit 1 - polarization V.
		 0 - means that antenna and angle are selected by algorithm;
		 1 - means that antenna and angle are forced by user."
	::= { cambiumAPConnectedSTAEntry 32 }

connectedSTASKU OBJECT-TYPE
	SYNTAX     Integer32 (0..255)
	MAX-ACCESS read-only
	STATUS     current
	DESCRIPTION
		"SKU Number of the connected SM
		Device Allocation: AP"
	::= { cambiumAPConnectedSTAEntry 33 }

connectedSTALinktestForceAllow OBJECT-TYPE
	SYNTAX     Integer32 (0..1)
	MAX-ACCESS read-only
	STATUS     current
	DESCRIPTION
		"Shows is force antenna allowed during linktest.
		0 - means that linktest have to run with default antenna
		1 - means that antenna can be selected during linktest"
	::= { cambiumAPConnectedSTAEntry 34 }

connectedSTAIPv6 OBJECT-TYPE
	SYNTAX	   Ipv6Address
	MAX-ACCESS read-only
	STATUS	   current
	DESCRIPTION
		"Connected SM WLAN IPv6 Address
		Device Allocation: AP"
	::= { cambiumAPConnectedSTAEntry 35 }

connectedSTAIsViaInterface OBJECT-TYPE
	SYNTAX     Integer32 (0..2)
	MAX-ACCESS read-only
	STATUS     current
	DESCRIPTION
		"Wireless interface number STA is visible via (starting from 0).
		Device Allocation: AP"
	::= { cambiumAPConnectedSTAEntry 36 }

connectedSTAMUMIMOGain OBJECT-TYPE
	SYNTAX     Integer32 (-1..100)
	MAX-ACCESS read-only
	STATUS     current
	DESCRIPTION
		"MU MIMO Gain for SM
		Device Allocation: AP"
	::= { cambiumAPConnectedSTAEntry 37 }

connectedSTAModelName OBJECT-TYPE
	SYNTAX	   DisplayString
	MAX-ACCESS read-only
	STATUS	   current
	DESCRIPTION
		"Connected SM Modelname.
		Device Allocation: AP"
	::= { cambiumAPConnectedSTAEntry 38 }

connectedSTAMUMIMOAzMetric OBJECT-TYPE
	SYNTAX     Integer32 (-128..127)
	MAX-ACCESS read-only
	STATUS     current
	DESCRIPTION
		"Azimuth metric for connected device.
		Azimuth metric always invalid for 11n devices(equals to -128).
		Device Allocation: AP"
	::= { cambiumAPConnectedSTAEntry 39 }

connectedSTAMUMIMOQuality OBJECT-TYPE
	SYNTAX     Integer32 (0..100)
	MAX-ACCESS read-only
	STATUS     current
	DESCRIPTION
		"MU MIMO Sounding Quality for SM
		Device Allocation: AP"
	::= { cambiumAPConnectedSTAEntry 40 }

connectedSTAMUMIMORate OBJECT-TYPE
	SYNTAX     Integer32 (0..7)
	MAX-ACCESS read-only
	STATUS     current
	DESCRIPTION
		"MU MIMO Sounding Rate for SM
		Device Allocation: AP"
	::= { cambiumAPConnectedSTAEntry 41 }

connectedSTAMUMIMOPairs OBJECT-TYPE
	SYNTAX     Integer32 (0..119)
	MAX-ACCESS read-only
	STATUS     current
	DESCRIPTION
		"MU MIMO pair count for SM
		Device Allocation: AP"
	::= { cambiumAPConnectedSTAEntry 42 }

connectedSTASoftwareVersion OBJECT-TYPE
	SYNTAX     DisplayString
	MAX-ACCESS read-only
	STATUS     current
	DESCRIPTION
		"Connected SM software version
		Device Allocation: AP"
	::= { cambiumAPConnectedSTAEntry 43 }

cambiumAPBridgeTable OBJECT-TYPE
	SYNTAX	   SEQUENCE OF CambiumAPBridgeEntry
	MAX-ACCESS not-accessible
	STATUS	   current
	DESCRIPTION
		"This table contains information relevant to the particular AP bridge
		 interfaces list:
			Bridge Name,
			Device MAC Address,
			Device Port,
			SM MAC Address,
			Aging Time in seconds
		Device Allocation: AP"
	::= { cambiumRFStatus 40 }

cambiumAPBridgeEntry OBJECT-TYPE
	SYNTAX	   CambiumAPBridgeEntry
	MAX-ACCESS not-accessible
	STATUS	   current
	DESCRIPTION
		"Interface list for particular bridge.
		Device Allocation: AP"
	INDEX	{ camAPBrTabDevMACAddress }
	::= { cambiumAPBridgeTable 1 }

CambiumAPBridgeEntry ::= SEQUENCE {
	camAPBrTabBridgeName	DisplayString,
	camAPBrTabDevMACAddress DisplayString,
	camAPBrTabDevPort		DisplayString,
	camAPBrTabSTAMACAddress DisplayString,
	camAPBrTabAgingTime		Counter32
}

camAPBrTabBridgeName OBJECT-TYPE
	SYNTAX	   DisplayString
	MAX-ACCESS read-only
	STATUS	   current
	DESCRIPTION
		"Bridge Name
		Device Allocation: AP"
	::= { cambiumAPBridgeEntry 1 }

camAPBrTabDevMACAddress OBJECT-TYPE
	SYNTAX	   DisplayString
	MAX-ACCESS read-only
	STATUS	   current
	DESCRIPTION
		"Device MAC Address
		Device Allocation: AP"
	::= { cambiumAPBridgeEntry 2 }

camAPBrTabDevPort OBJECT-TYPE
	SYNTAX	   DisplayString
	MAX-ACCESS read-only
	STATUS	   current
	DESCRIPTION
		"Device Port
		Device Allocation: AP"
	::= { cambiumAPBridgeEntry 3 }

camAPBrTabSTAMACAddress OBJECT-TYPE
	SYNTAX	   DisplayString
	MAX-ACCESS read-only
	STATUS	   current
	DESCRIPTION
		"SM MAC Address
		Device Allocation: AP"
	::= { cambiumAPBridgeEntry 4 }

camAPBrTabAgingTime OBJECT-TYPE
	SYNTAX	   Counter32
	MAX-ACCESS read-only
	STATUS	   current
	DESCRIPTION
		"Aging time in seconds
		Device Allocation: AP"
	::= { cambiumAPBridgeEntry 5 }

cambiumSTABridgeTable OBJECT-TYPE
	SYNTAX	   SEQUENCE OF CambiumSTABridgeEntry
	MAX-ACCESS not-accessible
	STATUS	   current
	DESCRIPTION
		"This table contains information relevant to the particular SM bridge
		 interfaces list:
			Bridge Name,
			Device MAC Address,
			Device Port,
			Aging Time in seconds
		Device Allocation: SM"
	::= { cambiumRFStatus 50 }

cambiumSTABridgeEntry OBJECT-TYPE
	SYNTAX	   CambiumSTABridgeEntry
	MAX-ACCESS not-accessible
	STATUS	   current
	DESCRIPTION
		"Interface list for particular bridge.
		Device Allocation: SM"
	INDEX	{ camSTABrTabDevMACAddress }
	::= { cambiumSTABridgeTable 1 }

CambiumSTABridgeEntry ::= SEQUENCE {
	camSTABrTabBridgeName		DisplayString,
	camSTABrTabDevMACAddress	DisplayString,
	camSTABrTabDevPort			DisplayString,
	camSTABrTabAgingTime		Counter32
}

camSTABrTabBridgeName OBJECT-TYPE
	SYNTAX	   DisplayString
	MAX-ACCESS read-only
	STATUS	   current
	DESCRIPTION
		"Bridge Name
		Device Allocation: SM"
	::= { cambiumSTABridgeEntry 1 }

camSTABrTabDevMACAddress OBJECT-TYPE
	SYNTAX	   DisplayString
	MAX-ACCESS read-only
	STATUS	   current
	DESCRIPTION
		"Device MAC Address
		Device Allocation: SM"
	::= { cambiumSTABridgeEntry 2 }

camSTABrTabDevPort OBJECT-TYPE
	SYNTAX	   DisplayString
	MAX-ACCESS read-only
	STATUS	   current
	DESCRIPTION
		"Device Port
		Device Allocation: SM"
	::= { cambiumSTABridgeEntry 3 }

camSTABrTabAgingTime OBJECT-TYPE
	SYNTAX	   Counter32
	MAX-ACCESS read-only
	STATUS	   current
	DESCRIPTION
		"Aging time in seconds
		Device Allocation: SM"
	::= { cambiumSTABridgeEntry 4 }

cambiumSTAMAC OBJECT-TYPE
	SYNTAX	   DisplayString (SIZE(17))
	MAX-ACCESS read-only
	STATUS	   current
	DESCRIPTION
		"String with dropped SM's MAC address
			 Device Allocation: AP"
	::= { cambiumRFStatus 60 }

cambiumSTADropReason OBJECT-TYPE
	SYNTAX	   DisplayString (SIZE(0..64))
	MAX-ACCESS read-only
	STATUS	   current
	DESCRIPTION
		"AP Reject reasons:
			1 - Max capacity reached
			2 - Software versions incompatible
			3 - ACL policy
			4 - STA in blacklist
			5 - Other reason
			6 - STA ranging failed
			7 - Malformed INAR
			8 - ePMP Elevate license exceeded
		 STA Association failure reasons:
			16 - INA retries exhausted
			17 - Out of cell
			18 - Error prop delay calculation
			19 - Lost AID
			20 - Authentication failed
			21 - Certificate check failed
			22 - Generic auth fail
			23 - MAC versions incompatible
			24 - INA response not received
			25 - Frame duration not supported
			30 - AP doesn't support reject reason
		 STA Disassociation reasons:
			32 - No allocation on AP
			33 - GPFs miss
			34 - BEACONs miss
			35 - STA has detected radar (ETSI)
			36 - STA initiated disconnect
			37 - AP parameters changed
			38 - Elevate auth failed due to packet loss
			39 - AP initiated disconnect by peer radio
			40 - STA KeepAlive RX stuck
			41 - Reconnect to Primary AP
		 AP Disassociation reasons:
			48 - Communication loss
			49 - Invalid key
			50 - Operator initiated disconnect
			51 - AP initiated disconnect
			52 - INAC miss timeout
			53 - AP KeepAlive RX stuck
			54 - AP Detected Radar
			55 - BSR miss
			56 - Group key update timeout"
	::= { cambiumRFStatus 61 }

cambiumNetworkEntryFailureSTAMAC OBJECT-TYPE
	SYNTAX	   DisplayString (SIZE(17))
	MAX-ACCESS read-only
	STATUS	   current
	DESCRIPTION
		"String with rejected SM's MAC
			 Device Allocation: AP "
	::= { cambiumRFStatus 62 }

cambiumNetworkEntryFailureReason OBJECT-TYPE
	SYNTAX	   DisplayString (SIZE(0..64))
	MAX-ACCESS read-only
	STATUS	   current
	DESCRIPTION
		"AP Reject reasons:
			1 - Max capacity reached
			2 - Software versions incompatible
			3 - PTP mode (ACL policy)
			4 - STA in blacklist
			5 - Other reason
			6 - STA ranging failed
			7 - Malformed INAR
			8 - ePMP Elevate license exceeded
		 STA Association failure reasons:
			16 - INA retries exhausted
			17 - Out of cell
			18 - Error prop delay calculation
			19 - Lost AID
			20 - Authentication failed
			21 - Certificate check failed
			22 - Generic auth fail
			23 - MAC versions incompatible
			24 - INA response not received
			25 - Frame duration not supported
			30 - AP doesn't support reject reason
		 STA Disassociation reasons:
			32 - No allocation on AP
			33 - GFPs miss
			34 - BEACONs miss
			35 - STA has detected radar (ETSI)
			36 - STA initiated disconnect
			37 - AP parameters changed
			38 - Elevate auth failed due to packet loss
			39 - AP initiated disconnect by peer radio
			40 - STA KeepAlive RX stuck
			41 - Reconnect to Primary AP
		 AP Disassociation reasons:
			48 - Communication loss
			49 - Invalid key
			50 - Operator initiated disconnect
			51 - AP initiated disconnect
			52 - INAC miss timeout
			53 - AP KeepAlive RX stuck
			54 - AP Detected Radar
			55 - BSR miss
			56 - Group key update timeout"
	::= { cambiumRFStatus 63 }

wirelessLinkDroppedCount OBJECT-TYPE
	SYNTAX	   Integer32
	MAX-ACCESS read-only
	STATUS	   current
	DESCRIPTION
		"Aggregated number of link SM <-> AP dropped
			 Device Allocation: AP, SM"
	::= { cambiumRFStatus 64 }

cambiumMUMIMOGainAggregated OBJECT-TYPE
	SYNTAX	   Integer32 (0..100)
	MAX-ACCESS read-only
	STATUS	   current
	DESCRIPTION
		"MU gain aggregated from all associated SMs
		Device Allocation: AP"
	::= { cambiumRFStatus 65 }

cambiumSTA2ConnectedRFFrequency OBJECT-TYPE
	SYNTAX	   Integer32 (2355..6420)
	MAX-ACCESS read-only
	STATUS	   current
	DESCRIPTION
		"Second Radio The frequency connected to AP
		Device Allocation: AP, SM"
	::= { cambiumRFStatus 101 }

cambiumSTA2ConnectedRFBandwidth OBJECT-TYPE
	SYNTAX	   Integer32 (1|2)
	MAX-ACCESS read-only
	STATUS	   current
	DESCRIPTION
		"Second Radio Connected RF Bandwidth:
			1 for 20 MHz,
			2 for 40 MHz,
			3 for 10 MHz,
			4 for 5  MHz,
			5 for 80 MHz
		Device Allocation: SM"
	::= { cambiumRFStatus 102 }

cambiumSTA2DLRSSI OBJECT-TYPE
	SYNTAX	   Integer32
	MAX-ACCESS read-only
	STATUS	   current
	DESCRIPTION
		"Second Radio SM RSSI in dBm
		Device Allocation: SM"
	::= { cambiumRFStatus 103 }

cambiumSTA2ConductedTXPower OBJECT-TYPE
	SYNTAX	   Integer32 (-25..30)
	MAX-ACCESS read-only
	STATUS	   current
	DESCRIPTION
		"Second Radio Current TX Power (Board Output Conducted) in dBm
		Device Allocation: SM"
	::= { cambiumRFStatus 105 }

cambiumSTA2UplinkMCSMode OBJECT-TYPE
	SYNTAX	   Integer32
	MAX-ACCESS read-only
	STATUS	   current
	DESCRIPTION
		"Second Radio UL MCS Mode:
			This parameter represents Uplink MCS mode number for both 802.11n and 802.11ac standard devices.

			802.11n HW:

			1  for MCS1,
			2  for MCS2,
			3  for MCS3,
			4  for MCS4,
			5  for MCS5,
			6  for MCS6,
			7  for MCS7,
			9  for MCS9,
			10 for MCS10,
			11 for MCS11,
			12 for MCS12,
			13 for MCS13,
			14 for MCS14,
			15 for MCS15,

			802.11ac HW:

			20 for 'SS MCS 0 - BPSK 1/2',
			21 for 'SS MCS 1 - QPSK 1/2',
			22 for 'SS MCS 2 - QPSK 3/4',
			23 for 'SS MCS 3 - 16-QAM 1/2',
			24 for 'SS MCS 4 - 16-QAM 3/4',
			25 for 'SS MCS 5 - 64-QAM 2/3',
			26 for 'SS MCS 6 - 64-QAM 3/4',
			27 for 'SS MCS 7 - 64-QAM 5/6',
			28 for 'SS MCS 8 - 256-QAM 3/4',
			29 for 'SS MCS 9 - 256-QAM 5/6',

			30 for 'DS MCS 0 - BPSK 1/2',
			31 for 'DS MCS 1 - QPSK 1/2',
			32 for 'DS MCS 2 - QPSK 3/4',
			33 for 'DS MCS 3 - 16-QAM 1/2',
			34 for 'DS MCS 4 - 16-QAM 3/4',
			35 for 'DS MCS 5 - 64-QAM 2/3',
			36 for 'DS MCS 6 - 64-QAM 3/4',
			37 for 'DS MCS 7 - 64-QAM 5/6',
			38 for 'DS MCS 8 - 256-QAM 3/4',
			39 for 'DS MCS 9 - 256-QAM 5/6'

		Device Allocation: SM"
	::= { cambiumRFStatus 106 }

cambiumSTA2DownlinkMCSMode OBJECT-TYPE
	SYNTAX	   Integer32
	MAX-ACCESS read-only
	STATUS	   current
	DESCRIPTION
		"Second Radio DL MCS Mode:
			This parameter represents Downlink MCS mode number for both 802.11n and 802.11ac standard devices.

			802.11n HW:

			1  for MCS1,
			2  for MCS2,
			3  for MCS3,
			4  for MCS4,
			5  for MCS5,
			6  for MCS6,
			7  for MCS7,
			9  for MCS9,
			10 for MCS10,
			11 for MCS11,
			12 for MCS12,
			13 for MCS13,
			14 for MCS14,
			15 for MCS15,

			802.11ac HW:

			20 for 'SS MCS 0 - BPSK 1/2',
			21 for 'SS MCS 1 - QPSK 1/2',
			22 for 'SS MCS 2 - QPSK 3/4',
			23 for 'SS MCS 3 - 16-QAM 1/2',
			24 for 'SS MCS 4 - 16-QAM 3/4',
			25 for 'SS MCS 5 - 64-QAM 2/3',
			26 for 'SS MCS 6 - 64-QAM 3/4',
			27 for 'SS MCS 7 - 64-QAM 5/6',
			28 for 'SS MCS 8 - 256-QAM 3/4',
			29 for 'SS MCS 9 - 256-QAM 5/6',

			30 for 'DS MCS 0 - BPSK 1/2',
			31 for 'DS MCS 1 - QPSK 1/2',
			32 for 'DS MCS 2 - QPSK 3/4',
			33 for 'DS MCS 3 - 16-QAM 1/2',
			34 for 'DS MCS 4 - 16-QAM 3/4',
			35 for 'DS MCS 5 - 64-QAM 2/3',
			36 for 'DS MCS 6 - 64-QAM 3/4',
			37 for 'DS MCS 7 - 64-QAM 5/6',
			38 for 'DS MCS 8 - 256-QAM 3/4',
			39 for 'DS MCS 9 - 256-QAM 5/6'

		Device Allocation: SM"
	::= { cambiumRFStatus 107 }

cambiumSTA2ConnectedAP OBJECT-TYPE
	SYNTAX	   DisplayString (SIZE(1..128))
	MAX-ACCESS read-only
	STATUS	   current
	DESCRIPTION
		"Second Radio Connected AP Name (SSID), If no AP is connected, Scanning should be returned
		Device Allocation: SM"
	::= { cambiumRFStatus 108 }

cambiumSTA2DLSNR OBJECT-TYPE
	SYNTAX	   Integer32
	MAX-ACCESS read-only
	STATUS	   current
	DESCRIPTION
		"Second Radio SM SNR in dBm
		Device Allocation: SM"
	::= { cambiumRFStatus 118 }

cambiumConnectedAP2MACAddress OBJECT-TYPE
	SYNTAX	   DisplayString (SIZE(0|11..17))
	MAX-ACCESS read-only
	STATUS	   current
	DESCRIPTION
		"Second Radio Connected AP MAC Address
		Device Allocation: SM"
	::= { cambiumRFStatus 119 }

sta2TxCapacity OBJECT-TYPE
	SYNTAX	   Integer32 (0..100)
	MAX-ACCESS read-only
	STATUS	   current
	DESCRIPTION
		"Second Radio TX Capacity for SM
		Device Allocation: SM"
	::= { cambiumRFStatus 121 }

sta2TxQuality OBJECT-TYPE
	SYNTAX	   Integer32 (0..100)
	MAX-ACCESS read-only
	STATUS	   current
	DESCRIPTION
		"Second Radio TX Quality for SM
		Device Allocation: SM"
	::= { cambiumRFStatus 122 }

cambiumRSSI2Ch0 OBJECT-TYPE
	SYNTAX	   Integer32
	MAX-ACCESS read-only
	STATUS	   current
	DESCRIPTION
		"Second radio RSSI at chain 0 in dBm
		Device Allocation: AP (PTP mode), SM"
	::= { cambiumRFStatus 124 }

cambiumRSSI2Ch1 OBJECT-TYPE
	SYNTAX	   Integer32
	MAX-ACCESS read-only
	STATUS	   current
	DESCRIPTION
		"Second radio RSSI at chain 1 in dBm
		Device Allocation: AP (PTP mode), SM"
	::= { cambiumRFStatus 125 }

cambiumGPSCurrentSyncState OBJECT-TYPE
	SYNTAX	   Integer32 (0..5)
	MAX-ACCESS read-only
	STATUS	   current
	DESCRIPTION
		"GPS Current SYNC State:
			0 - The Initialization State
			1 - The No Synchronization State
			2 - The Synchronization State
			3 - The Hold Off State
			4 - The Regaining Sync State
			5 - The Free Run State
		Device Allocation: AP"
	::= { cambiumGPSStatus 1 }

cambiumGPSLatitude OBJECT-TYPE
	SYNTAX	   DisplayString (SIZE(0..128))
	MAX-ACCESS read-only
	STATUS	   current
	DESCRIPTION
		"Current location information from GPS Device. GPS cordinates (latitude).
		Device Allocation: AP, SM"
	::= { cambiumGPSStatus 2 }

cambiumGPSLongitude OBJECT-TYPE
	SYNTAX	   DisplayString (SIZE(0..128))
	MAX-ACCESS read-only
	STATUS	   current
	DESCRIPTION
		"Current location information from GPS Device. GPS cordinates (longitude).
		Device Allocation: AP, SM"
	::= { cambiumGPSStatus 3 }

cambiumGPSHeight OBJECT-TYPE
	SYNTAX	   DisplayString (SIZE(0..128))
	MAX-ACCESS read-only
	STATUS	   current
	DESCRIPTION
		"Current location information from GPS Device. GPS coordinates (Height).
		Device Allocation: AP, SM"
	::= { cambiumGPSStatus 4 }

cambiumGPSTime OBJECT-TYPE
	SYNTAX	   DisplayString (SIZE(0..128))
	MAX-ACCESS read-only
	STATUS	   current
	DESCRIPTION
		"Current Time/Date information from GPS Device. GPS (Time).
		Device Allocation: AP, SM"
	::= { cambiumGPSStatus 5 }

cambiumGPSNumTrackedSat OBJECT-TYPE
	SYNTAX	   Integer32 (1..128)
	MAX-ACCESS read-only
	STATUS	   current
	DESCRIPTION
		"Current Satellite information from GPS Device. GPS (Number of Satellites Tracked).
		Device Allocation: AP, SM"
	::= { cambiumGPSStatus 6 }

cambiumGPSNumVisibleSat OBJECT-TYPE
	SYNTAX	   Integer32 (1..128)
	MAX-ACCESS read-only
	STATUS	   current
	DESCRIPTION
		"Current Satellite information from GPS Device. GPS (Number of Satellites Visible).
		Device Allocation: AP, SM"
	::= { cambiumGPSStatus 7 }

cambiumGPSSatSNRTable OBJECT-TYPE
	SYNTAX SEQUENCE OF CambiumGPSSatSNREntry
	MAX-ACCESS not-accessible
	STATUS	   current
	DESCRIPTION
		"Table of Current Satellite information from GPS Device. GPS (SNR of Satellites).
		Device Allocation: AP, SM"
	::= { cambiumGPSStatus 8 }

cambiumGPSSatSNREntry OBJECT-TYPE
	SYNTAX	   CambiumGPSSatSNREntry
	MAX-ACCESS not-accessible
	STATUS	   current
	DESCRIPTION
		"Satellite SNR values for Visible and Tracked Satellites
		Device Allocation: AP"
	INDEX	 { gpsSatelliteId }
	::= { cambiumGPSSatSNRTable 1 }

CambiumGPSSatSNREntry  ::= SEQUENCE {
	gpsSatelliteId Integer32,
	gpsSnrValue Integer32,
	gpsSatelliteStatus Integer32
}

gpsSatelliteId OBJECT-TYPE
	SYNTAX Integer32 (0..255)
	MAX-ACCESS read-only
	STATUS	 current
	DESCRIPTION
		"Satellite ID for which SNR is displayed"
	::= {cambiumGPSSatSNREntry 1 }

gpsSnrValue OBJECT-TYPE
	SYNTAX Integer32 (0..99)
	MAX-ACCESS read-only
	STATUS current
	DESCRIPTION
		"SNR value for a satellite"
	::= {cambiumGPSSatSNREntry 2 }

gpsSatelliteStatus OBJECT-TYPE
	SYNTAX Integer32 (1|2)
	MAX-ACCESS read-only
	STATUS current
	DESCRIPTION
		"Satellite Status whether they are visible or tracked
		 1 - Visible
		 2 - Tracked"
	DEFVAL { 1 }
	::= {cambiumGPSSatSNREntry	3}

cambiumGPSDeviceInfo OBJECT-TYPE
	SYNTAX	   DisplayString (SIZE(0..128))
	MAX-ACCESS read-only
	STATUS	   current
	DESCRIPTION
		"GPS Device Information
		Device Allocation: AP, SM"
	::= { cambiumGPSStatus 9 }

cambiumGPSFirmwareUpdateStatus	OBJECT-TYPE
	SYNTAX	   Integer32 (0..10)
	MAX-ACCESS read-only
	STATUS	   current
	DESCRIPTION
		"Software Update Status OID
			0 - No GPS FW Update is progress or No FW update is required,
			1 - GPS FW Update is in progress, Uploading SW package to device,
			2 - GPS FW Update is in progress, Verifying SHA2 signature,
			3 - GPS FW Update is in progress, Executing pre-update script,
			4 - GPS FW Update is in progress, Uploading Firmware to GPS device,
			5 - GPS FW Update is in progress, Uploading Firmware to GPS device,
			6 - GPS FW Update is in progress, Executing post-update script,
			7 - GPS FW Update is finished, waiting for reboot,
			8 - GPS FW Update is Required, Please upgrade to latest GPS FW,
		When GPS FW Update is successfully, return value is 7,
		GUI or NMS indicate that GPS FW update was successful,
		Device can be rebooted.
		Device Allocation: AP, SM"
	::= { cambiumGPSStatus 10}

cambiumGPSAntennaType OBJECT-TYPE
	SYNTAX	   DisplayString (SIZE(0..8))
	MAX-ACCESS read-only
	STATUS	   current
	DESCRIPTION
		"Antenna type: Internal or External.
		Empty string if GPS chip does not support Antenna type command.
		Device Allocation: AP, SM"
	::= { cambiumGPSStatus 11}

tddSyncInternalStateDur OBJECT-TYPE
	SYNTAX    Integer32
	MAX-ACCESS read-only
	STATUS     current
	DESCRIPTION
		"Internal state duration, ms
		Device Allocation: AP"
	::= { cambiumGPSStatus 12 }

tddSyncExpectedDrift OBJECT-TYPE
	SYNTAX    Integer32
	MAX-ACCESS read-only
	STATUS     current
	DESCRIPTION
		"An expected drift, ns
		Device Allocation: AP"
	::= { cambiumGPSStatus 13 }

tddSyncExpectedJitter OBJECT-TYPE
	SYNTAX    Integer32
	MAX-ACCESS read-only
	STATUS     current
	DESCRIPTION
		"An expected jitter, ns
		Device Allocation: AP"
	::= { cambiumGPSStatus 14 }

tddSyncStatTable OBJECT-TYPE
	SYNTAX SEQUENCE OF TddSyncStatEntry
	MAX-ACCESS not-accessible
	STATUS     current
	DESCRIPTION
		"TDD Sync Statistics
		Device Allocation: AP"
	::= { cambiumGPSStatus 15 }

tddSyncStatEntry OBJECT-TYPE
	SYNTAX     TddSyncStatEntry
	MAX-ACCESS not-accessible
	STATUS     current
	DESCRIPTION
		"TDD Sync statistics
		Device Allocation: AP"
	INDEX	{ tddSyncStatPeriod }
	::= { tddSyncStatTable 1 }

TddSyncStatEntry ::= SEQUENCE {
	tddSyncStatPeriod
	INTEGER,
	tddSyncPulseCount
	    Counter32,
	tddSyncLostPulseCount
		Counter32,
	tddSyncInvalidPulseCount
		Counter32,
	tddSyncInvPulseDeviationMin
		Integer32,
	tddSyncInvPulseDeviationMax
		Integer32,
	tddSyncInvPulseDeviationAvgAbs
		Integer32,
	tddSyncDriftMin
		Integer32,
	tddSyncDriftMax
		Integer32,
	tddSyncDriftAvg
		Integer32,
	tddSyncJitterMin
		Integer32,
	tddSyncJitterMax
		Integer32,
	tddSyncJitterAvgAbs
		Integer32,
	tddSyncState1Count
		Counter32,
	tddSyncState1Duration
		Counter32,
	tddSyncState2Count
		Counter32,
	tddSyncState2Duration
		Counter32,
	tddSyncState3Count
		Counter32,
	tddSyncState3Duration
		Counter32
}

tddSyncStatPeriod OBJECT-TYPE
	SYNTAX    INTEGER {
				minutes5(1), -- statistics for last 5 minutes
				hours1(2),   -- statistics for last hour  (+- 5 minutes)
				hours24(3),  -- statistics for last 24 hours (+- 1hour)
				alltime(4)   -- statistics for all the time
			  }
	MAX-ACCESS read-only
	STATUS     current
	DESCRIPTION
		"The Time period the Sync statistics is taken for
		Device Allocation: AP"
	::= {tddSyncStatEntry 1}

tddSyncPulseCount OBJECT-TYPE
	SYNTAX     Counter32
	MAX-ACCESS read-only
	STATUS     current
	DESCRIPTION
		"Lost Sync pulses number
		Device Allocation: AP"
	::= {tddSyncStatEntry 2}

tddSyncLostPulseCount OBJECT-TYPE
	SYNTAX     Counter32
	MAX-ACCESS read-only
	STATUS     current
	DESCRIPTION
		"Lost Sync pulses number
		Device Allocation: AP"
	::= {tddSyncStatEntry 3}

tddSyncInvalidPulseCount OBJECT-TYPE
	SYNTAX     Counter32
	MAX-ACCESS read-only
	STATUS     current
	DESCRIPTION
		"Invalid Sync pulses number
		Device Allocation: AP"
	::= {tddSyncStatEntry 4}

tddSyncInvPulseDeviationMin OBJECT-TYPE
	SYNTAX     Integer32
	MAX-ACCESS read-only
	STATUS     current
	DESCRIPTION
		"Invalid Syns pulses minimal deviation from (1s + drift)
		Device Allocation: AP"
	::= {tddSyncStatEntry 5}

tddSyncInvPulseDeviationMax OBJECT-TYPE
	SYNTAX     Integer32
	MAX-ACCESS read-only
	STATUS     current
	DESCRIPTION
		"Invalid Syns pulses maximal deviation from (1s + drift)
		Device Allocation: AP"
	::= {tddSyncStatEntry 6}

tddSyncInvPulseDeviationAvgAbs OBJECT-TYPE
	SYNTAX     Integer32 (0..2147483647)
	MAX-ACCESS read-only
	STATUS     current
	DESCRIPTION
		"Invalid Syns pulses average deviation by modulo from (1s + drift)
		Device Allocation: AP"
	::= {tddSyncStatEntry 7}

tddSyncDriftMin OBJECT-TYPE
	SYNTAX     Integer32
	MAX-ACCESS read-only
	STATUS     current
	DESCRIPTION
		"Minimal drift of Sync pulses, ns
		Device Allocation: AP"
	::= {tddSyncStatEntry 8}

tddSyncDriftMax OBJECT-TYPE
	SYNTAX     Integer32
	MAX-ACCESS read-only
	STATUS     current
	DESCRIPTION
		"Maximal drift of Sync pulses, ns
		Device Allocation: AP"
	::= {tddSyncStatEntry 9}

tddSyncDriftAvg OBJECT-TYPE
	SYNTAX     Integer32
	MAX-ACCESS read-only
	STATUS     current
	DESCRIPTION
		"Average drift of Sync pulses, ns
		Device Allocation: AP"
	::= {tddSyncStatEntry 10}

tddSyncJitterMin OBJECT-TYPE
	SYNTAX     Integer32
	MAX-ACCESS read-only
	STATUS     current
	DESCRIPTION
		"Minimal jitter of Sync pulses, ns
		Device Allocation: AP"
	::= {tddSyncStatEntry 11}

tddSyncJitterMax OBJECT-TYPE
	SYNTAX     Integer32
	MAX-ACCESS read-only
	STATUS     current
	DESCRIPTION
		"Maximal jitter of Sync pulses, ns
		Device Allocation: AP"
	::= {tddSyncStatEntry 12}

tddSyncJitterAvgAbs OBJECT-TYPE
	SYNTAX     Integer32 (0..2147483647)
	MAX-ACCESS read-only
	STATUS     current
	DESCRIPTION
		"Average jitter by modulo of Sync pulses, ns
		Device Allocation: AP"
	::= {tddSyncStatEntry 13}

tddSyncState1Count OBJECT-TYPE
	SYNTAX     Counter32
	MAX-ACCESS read-only
	STATUS     current
	DESCRIPTION
		"How many times we switched to state #1
		Device Allocation: AP"
	::= {tddSyncStatEntry 14}

tddSyncState1Duration OBJECT-TYPE
	SYNTAX     Counter32
	MAX-ACCESS read-only
	STATUS     current
	DESCRIPTION
		"How many times we spent in state #1
		Device Allocation: AP"
	::= {tddSyncStatEntry 15}

tddSyncState2Count OBJECT-TYPE
	SYNTAX     Counter32
	MAX-ACCESS read-only
	STATUS     current
	DESCRIPTION
		"How many times we switched to state #2
		Device Allocation: AP"
	::= {tddSyncStatEntry 16}

tddSyncState2Duration OBJECT-TYPE
	SYNTAX     Counter32
	MAX-ACCESS read-only
	STATUS     current
	DESCRIPTION
		"How many times we spent in state #2
		Device Allocation: AP"
	::= {tddSyncStatEntry 17}

tddSyncState3Count OBJECT-TYPE
	SYNTAX     Counter32
	MAX-ACCESS read-only
	STATUS     current
	DESCRIPTION
		"How many times we switched to state #3
		Device Allocation: AP"
	::= {tddSyncStatEntry 18}

tddSyncState3Duration OBJECT-TYPE
	SYNTAX     Counter32
	MAX-ACCESS read-only
	STATUS     current
	DESCRIPTION
		"How many time we spent in state #3
		Device Allocation: AP"
	::= {tddSyncStatEntry 19}

cambiumLANStatus OBJECT-TYPE
	SYNTAX	   Integer32 (0|1|2)
	MAX-ACCESS read-only
	STATUS	   current
	DESCRIPTION
		"Use the RFC-1213 ifTable to view the physical port status.
		This attribute indicates the Linux driver status of the port.
		LAN Status:
			0 - Down,
			1 - Up,
			2 - Disabled
		Device Allocation: AP, SM"
	::= { cambiumLinkStatus 1 }

cambiumWLANStatus OBJECT-TYPE
	SYNTAX	   Integer32 (0|1|2)
	MAX-ACCESS read-only
	STATUS	   current
	DESCRIPTION
		"WLAN Status:
			0 - Down,
			1 - Up
		Device Allocation: AP, SM"
	::= { cambiumLinkStatus 2 }

cambiumEffectiveDeviceIPAddress OBJECT-TYPE
	SYNTAX	   IpAddress
	MAX-ACCESS read-only
	STATUS	   current
	DESCRIPTION
		"Current Device IP address
		Device Allocation: AP, SM"
	::= { cambiumLinkStatus 3 }

cambiumEffectiveSTANetworkMode OBJECT-TYPE
	SYNTAX	   Integer32 (1|2|3)
	MAX-ACCESS read-only
	STATUS	   current
	DESCRIPTION
		"Effective SM Network Mode:
			1 - NAT,
			2 - Bridge,
			3 - Router
		Device Allocation: SM"
	::= { cambiumLinkStatus 4 }

cambiumEffectiveDeviceLANNetMask OBJECT-TYPE
	SYNTAX	   IpAddress
	MAX-ACCESS read-only
	STATUS	   current
	DESCRIPTION
		"Current Device Network Mask
		Device Allocation: AP, SM"
	::= { cambiumLinkStatus 5 }

cambiumEffectiveDeviceDefaultGateWay OBJECT-TYPE
	SYNTAX	   IpAddress
	MAX-ACCESS read-only
	STATUS	   current
	DESCRIPTION
		"Effective Device Default Gateway IP Address,
		NOTE: This parameters lists only the first gateway IP
		Device Allocation: AP, SM"
	::= { cambiumLinkStatus 6 }

cambiumEffectiveDeviceDNSIPAddress OBJECT-TYPE
	SYNTAX	   IpAddress
	MAX-ACCESS read-only
	STATUS	   current
	DESCRIPTION
		"Current Device DNS IP Address,
		NOTE: This parameter displays only the first DNS IP
		Device Allocation: AP, SM"
	::= { cambiumLinkStatus 7 }

cambiumEffectiveWANIPAddress OBJECT-TYPE
	SYNTAX	   IpAddress
	MAX-ACCESS read-only
	STATUS	   current
	DESCRIPTION
		"Current Device WLAN IP address
		Device Allocation: SM"
	::= { cambiumLinkStatus 8 }

cambiumEffectiveDeviceWANNetMask OBJECT-TYPE
	SYNTAX	   IpAddress
	MAX-ACCESS read-only
	STATUS	   current
	DESCRIPTION
		"Current Device Network Mask
		Device Allocation: SM"
	::= { cambiumLinkStatus 9 }

cambiumEffectiveDeviceWANPPPoEStatus OBJECT-TYPE
	SYNTAX	   Integer32 (0|1)
	MAX-ACCESS read-only
	STATUS	   current
	DESCRIPTION
		"WAN PPPoE Status:
			0 - Disabled
			1 - Enabled-Connected
			2 - Enabled-Connecting
			3 - Enabled-Disconnected
		Device Allocation: SM"
	DEFVAL	{ 0 }
	::= { cambiumLinkStatus 10 }

cambiumLANModeStatus  OBJECT-TYPE
	SYNTAX	   Integer32 (-1|0|1)
	MAX-ACCESS read-only
	STATUS	   current
	DESCRIPTION
		"LAN Mode Status
			-1 - No data,
			 0 - Half,
			 1 - Full
		Device Allocation: AP, SM"
	::= { cambiumLinkStatus 11 }

cambiumLANSpeedStatus  OBJECT-TYPE
	SYNTAX	   Integer32 (-1|10|100|1000)
	MAX-ACCESS read-only
	STATUS	   current
	DESCRIPTION
		"LAN Speed Status
			-1 - No data,
			 10 - 10 Mb/s,
			 100 - 100 Mb/s,
			 1000 - 1000 Mb/s
		Device Allocation: AP, SM"
	::= { cambiumLinkStatus 12 }

cambiumDHCPOption82Status OBJECT-TYPE
	SYNTAX	   Integer32 (0|1)
	MAX-ACCESS read-only
	STATUS	   current
	DESCRIPTION
		"DHCP Option82 Status:
			0 - Disabled
			1 - Enabled
		Device Allocation: AP"
	::= { cambiumLinkStatus 13 }

cambiumLAN2ModeStatus  OBJECT-TYPE
	SYNTAX	   Integer32 (-1|0|1)
	MAX-ACCESS read-only
	STATUS	   current
	DESCRIPTION
		"2nd LAN Mode Status
			-1 - No data,
			 0 - Half,
			 1 - Full
		Device Allocation: AP, SM"
	::= { cambiumLinkStatus 14 }

cambiumLAN2SpeedStatus  OBJECT-TYPE
	SYNTAX	   Integer32 (-1|10|100|1000|10000)
	MAX-ACCESS read-only
	STATUS	   current
	DESCRIPTION
		"2nd LAN Speed Status
			-1 - No data,
			 10 - 10 Mb/s,
			 100 - 100 Mb/s,
			 1000 - 1000 Mb/s,
			 10000 - 10000 Mb/s
		Device Allocation: AP, SM"
	::= { cambiumLinkStatus 15 }

cambiumLAN2Status OBJECT-TYPE
	SYNTAX	   Integer32 (0|1|2)
	MAX-ACCESS read-only
	STATUS	   current
	DESCRIPTION
		"Use the RFC-1213 ifTable to view the physical port status.
		This attribute indicates the Linux driver status of the port.
		2nd LAN Status:
			0 - Down,
			1 - Up,
			2 - Disabled
		Device Allocation: AP, SM"
	::= { cambiumLinkStatus 16 }

cambiumDHCPOption66Status OBJECT-TYPE
	SYNTAX	   Integer32 (0|1|2)
	MAX-ACCESS read-only
	STATUS	   current
	DESCRIPTION
		"DHCP Option66 Status:
		0 - Disabled,
		1 - Enabled. No Configuration is received,
		2 - Enabled. Configuration received
		Device Allocation: AP, SM"
	::= { cambiumLinkStatus 17 }

cambiumDHCPOption66URL OBJECT-TYPE
	SYNTAX	   DisplayString (SIZE(0..128))
	MAX-ACCESS read-only
	STATUS	   current
	DESCRIPTION
		"DHCP Option66 URL:
		 This specifies the URL for accessing JSON configuration file
		Device Allocation: AP, SM"
	::= { cambiumLinkStatus 18 }

cambiumDHCPOption66Error OBJECT-TYPE
	SYNTAX	   Integer32 (0|1|2)
	MAX-ACCESS read-only
	STATUS	   current
	DESCRIPTION
		"DHCP Option66 Error:
			0 - No Errors,
			1 - Configuration Download failed,
			2 - Configuration Apply failed
		Device Allocation: AP, SM"
	::= { cambiumLinkStatus 19 }

cambiumARPTable	 OBJECT-TYPE
	SYNTAX SEQUENCE OF CambiumARPEntry
	MAX-ACCESS not-accessible
	STATUS	   current
	DESCRIPTION
		"Neibour devices IP/MAC pair
		 Table"
	::= { cambiumLinkStatus 20 }

cambiumDHCPOption43URL OBJECT-TYPE
	SYNTAX	   DisplayString (SIZE(0..128))
	MAX-ACCESS read-only
	STATUS	   current
	DESCRIPTION
		"DHCP Option43 URL:
		 It specifies a URL to access cnMaestro.
		Device Allocation: AP, SM"
	::= { cambiumLinkStatus 21 }

cambiumManagementIFStatus OBJECT-TYPE
	SYNTAX	   Integer32 (0|1)
	MAX-ACCESS read-only
	STATUS	   current
	DESCRIPTION
		"Separate Management Interface Status:
			0 - Down,
			1 - Up
		Device Allocation: SM"
	::= { cambiumLinkStatus 25 }

cambiumManagementIFIPAddress OBJECT-TYPE
	SYNTAX	   IpAddress
	MAX-ACCESS read-only
	STATUS	   current
	DESCRIPTION
		"Current Device Separate Management IP address
		Device Allocation: SM"
	::= { cambiumLinkStatus 26 }

cambiumManagementIFNetMask OBJECT-TYPE
	SYNTAX	   IpAddress
	MAX-ACCESS read-only
	STATUS	   current
	DESCRIPTION
		"Current Device Separate Management Network Mask
		Device Allocation: SM"
	::= { cambiumLinkStatus 27 }

cambiumManagementIFGateway OBJECT-TYPE
	SYNTAX	   IpAddress
	MAX-ACCESS read-only
	STATUS	   current
	DESCRIPTION
		"Current Device Separate Management Gateway
		Device Allocation: SM"
	::= { cambiumLinkStatus 28 }

cambiumEffectiveNetworkLanMTU OBJECT-TYPE
	SYNTAX	   Integer32 (0|576..3508)
	MAX-ACCESS read-only
	STATUS	   current
	DESCRIPTION
		"SM NAT LAN MTU size
		For Force devices this value is limited to 1700
		Device Allocation: SM"
	DEFVAL	{ 1500 }
	::= { cambiumLinkStatus 29 }

cambiumEffectiveNetworkBridgeMTU OBJECT-TYPE
	SYNTAX	   Integer32 (0|576..3508)
	MAX-ACCESS read-only
	STATUS	   current
	DESCRIPTION
		"Device Bridge MTU size
		For Force devices this value is limited to 1700
		Device Allocation: AP, SM"
	DEFVAL	{ 1500 }
	::= { cambiumLinkStatus 30 }

cambiumStaticRoutesTable  OBJECT-TYPE
	SYNTAX SEQUENCE OF CambiumStaticRoutesEntry
	MAX-ACCESS not-accessible
	STATUS	   current
	DESCRIPTION
		"Static Routes Table"
	::= { cambiumLinkStatus 31 }

cambiumIPAliasTable OBJECT-TYPE
	SYNTAX SEQUENCE OF CambiumIPAliasEntry
	MAX-ACCESS not-accessible
	STATUS	   current
	DESCRIPTION
		"IP aliases list table.
		Device Allocation: AP, SM"
	::= { cambiumLinkStatus 32 }

cambiumCnsServConsStat OBJECT-TYPE
	SYNTAX	   DisplayString (SIZE(0..128))
	MAX-ACCESS read-only
	STATUS	   current
	DESCRIPTION
		"cnMaestro Connection Status:
		Cambium provides cloud management of Cambium devices, called cnMaestro.
		This describes the state of the connection to the cnMaestro"
	::= { cambiumLinkStatus 33 }

cambiumCnsServAccountID  OBJECT-TYPE
	SYNTAX	   DisplayString (SIZE(0..128))
	MAX-ACCESS read-only
	STATUS	   current
	DESCRIPTION
		"cnMaestro Account ID:
		Displays cnMaestro Account ID,
		This is the account ID for the customer.
		It is returned from the cloud management system."
	::= { cambiumLinkStatus 34 }

cambiumAPCnsMGMTState  OBJECT-TYPE
	SYNTAX	   Integer32 (0..1)
	MAX-ACCESS read-only
	STATUS	   current
	DESCRIPTION
		"AP Device management State"
	::= { cambiumLinkStatus 35 }

cambiumEffectiveDeviceIPv6Address OBJECT-TYPE
	SYNTAX     Ipv6Address
	MAX-ACCESS read-only
	STATUS     current
	DESCRIPTION
		"Current Device IPv6 address
		Device Allocation: AP, SM"
	::= { cambiumLinkStatus 36 }

cambiumLinkLocalDeviceIPv6Address OBJECT-TYPE
	SYNTAX     Ipv6Address
	MAX-ACCESS read-only
	STATUS     current
	DESCRIPTION
		"Device Link Local IPv6 address
		Device Allocation: AP, SM"
	::= { cambiumLinkStatus 37 }

cambiumEffectiveWANIPv6Address OBJECT-TYPE
	SYNTAX     Ipv6Address
	MAX-ACCESS read-only
	STATUS     current
	DESCRIPTION
		"Current Device WLAN IPv6 address
		Device Allocation: SM"
	::= { cambiumLinkStatus 38 }

cambiumLinkLocalWANIPv6Address OBJECT-TYPE
	SYNTAX     Ipv6Address
	MAX-ACCESS read-only
	STATUS     current
	DESCRIPTION
		"Current Device WLAN Link Local IPv6 address
		Device Allocation: SM"
	::= { cambiumLinkStatus 39 }

cambiumManagementIFIPv6Address OBJECT-TYPE
	SYNTAX     Ipv6Address
	MAX-ACCESS read-only
	STATUS     current
	DESCRIPTION
		"Current Device Separate Management IPv6 address
		Device Allocation: SM"
	::= { cambiumLinkStatus 40 }

cambiumLinkLocalManagementIFIPv6Address OBJECT-TYPE
	SYNTAX     Ipv6Address
	MAX-ACCESS read-only
	STATUS     current
	DESCRIPTION
		"Current Device Separate Management Link Local IPv6 address
		Device Allocation: SM"
	::= { cambiumLinkStatus 41 }

cambiumEffectiveDeviceIPv6DefaultGateWay OBJECT-TYPE
	SYNTAX     Ipv6Address
	MAX-ACCESS read-only
	STATUS     current
	DESCRIPTION
		"Effective Device Gateway IPv6 Address,
		NOTE: This parameters lists only the first gateway IPv6
		for Bridge and NAT/Router modes.
		Device Allocation: AP, SM"
	::= { cambiumLinkStatus 42 }

cambiumManagementIFIPv6Gateway OBJECT-TYPE
	SYNTAX     Ipv6Address
	MAX-ACCESS read-only
	STATUS     current
	DESCRIPTION
		"Current Device Separate Management IPv6 Gateway
		Device Allocation: SM"
	::= { cambiumLinkStatus 43 }

cambiumSFPConnectorType OBJECT-TYPE
	SYNTAX     Integer32 (0..255)
	MAX-ACCESS read-only
	STATUS     current
	DESCRIPTION
		"SFP connection type
		 0 - Unknown or unspecified,
		 1 - SC,
		 2 - Fibre Channel Style 1 copper connector,
		 3 - Fibre Channel Style 2 copper connector,
		 4 - BNC/TNC,
		 5 - Fibre Channel coaxial headers,
		 6 - FiberJack,
		 7 - LC,
		 8 - MT-RJ,
		 9 - MU,
		 10 - SG,
		 11 - Optical pigtail,
		 12 - MPO Parallel Optic,
		 13-31 - Reserved, Unallocated,
		 32 - HSSDC II,
		 33 - Copper Pigtail,
		 34 -  RJ45,
		 35-127 - Reserved, Unallocated,
		 128-255 - Vendor specific
		Device Allocation: AP, SM"
	::= { cambiumLinkStatus 44 }

cambiumSFPEthernetCodes OBJECT-TYPE
	SYNTAX      Integer32 (0..13)
	MAX-ACCESS read-only
	STATUS     current
	DESCRIPTION
		"SFP ethernet codes
		 0 - 1000BASE-SX,
		 1 - 1000BASE-LX,
		 2 - 1000BASE-CX,
		 3 - 1000BASE-T,
		 4 - 100BASE-LX/LX10,
		 5 - 100BASE-FX,
		 6 - BASE-BX10,
		 7 - BASE-PX
		 8 - 10G BASE-SR
		 9 - 10G BASE-LR
		 10 - 10G BASE-LRM
		 11 - 10G BASE-ER
		 12 - SFP+ Passive Cable
		 13 - SFP+ Active Cable
		Device Allocation: AP, SM"
	::= { cambiumLinkStatus 45 }

cambiumSFPEncodingCodes OBJECT-TYPE
	SYNTAX      Integer32 (0..6)
	MAX-ACCESS read-only
	STATUS     current
	DESCRIPTION
		"SFP encoding codes
		 0 - Unspecified,
		 1 - 8B10B,
		 2 - 4B5B,
		 3 - NRZ,
		 4 - Manchester,
		 5 - SONET Scrambled,
		 6 -  64B/66B
		Device Allocation: AP, SM"
	::= { cambiumLinkStatus 46 }

cambiumSFPBRNominal OBJECT-TYPE
	SYNTAX      Integer32
	MAX-ACCESS read-only
	STATUS     current
	DESCRIPTION
		"The nominal bit rate (BR, nominal)
		is specified in units of 100 Megabits per second,
		rounded off to the nearest 100 Megabits per second.
		Device Allocation: AP, SM"
	::= { cambiumLinkStatus 47 }

cambiumSFPVendorName OBJECT-TYPE
	SYNTAX     DisplayString (SIZE(0..16))
	MAX-ACCESS read-only
	STATUS     current
	DESCRIPTION
		"SFP vendor name (ASCII)
		Device Allocation: AP, SM"
	::= { cambiumLinkStatus 48 }

cambiumSFPVendorOUI OBJECT-TYPE
	SYNTAX     DisplayString (SIZE(0|8))
	MAX-ACCESS read-only
	STATUS     current
	DESCRIPTION
		"SFP vendor IEEE company ID
		Device Allocation: AP, SM"
	::= { cambiumLinkStatus 49 }

cambiumSFPVendorPN OBJECT-TYPE
	SYNTAX     DisplayString (SIZE(0..16))
	MAX-ACCESS read-only
	STATUS     current
	DESCRIPTION
		"Part number provided by SFP vendor (ASCII)
		Device Allocation: AP, SM"
	::= { cambiumLinkStatus 50 }

cambiumEffectiveNetworkLan2MTU OBJECT-TYPE
	SYNTAX     Integer32 (0|576..3508)
	MAX-ACCESS read-only
	STATUS     current
	DESCRIPTION
		"SM NAT LAN2 MTU size
		For Force devices this value is limited to 1700
		Device Allocation: SM"
	DEFVAL  { 1500 }
	::= { cambiumLinkStatus 51 }

cambiumEffectiveManagementIFIPv6Address OBJECT-TYPE
	SYNTAX     Ipv6Address
	MAX-ACCESS read-only
	STATUS     current
	DESCRIPTION
		"Current Device IPv6 address
		Device Allocation: AP, SM"
	::= { cambiumLinkStatus 52 }

cambiumLanIPv6PrefixDelegated OBJECT-TYPE
	SYNTAX     Ipv6Address
	MAX-ACCESS read-only
	STATUS     current
	DESCRIPTION
		"Prefix Delegated IPv6 Address for LAN interface
		Device Allocation: SM"
	::= { cambiumLinkStatus 53 }

lanSwitchPortsNum OBJECT-TYPE
	SYNTAX     Integer32 (0..32)
	MAX-ACCESS read-only
	STATUS     current
	DESCRIPTION
		"Number of physical Switch Ports
		Device Allocation: AP, SM"
	DEFVAL  { 4 }
	::= { cambiumLinkStatus 60 }

lanSwitchPortStatusTable OBJECT-TYPE
	SYNTAX SEQUENCE OF LanSwitchPortStatusEntry
	MAX-ACCESS not-accessible
	STATUS     current
	DESCRIPTION
		"Switch Port Table Status"
	::= { cambiumLinkStatus 61 }

lanSwitchPortStatusEntry OBJECT-TYPE
	SYNTAX     LanSwitchPortStatusEntry
	MAX-ACCESS not-accessible
	STATUS     current
	DESCRIPTION
		"Switch Port Status Entry
		Device Allocation: AP, SM"
	INDEX	{ lanSwitchPortsNum }
	::= { lanSwitchPortStatusTable 1 }

LanSwitchPortStatusEntry ::= SEQUENCE {
	lanSwitchPortCAPS
		Integer32,
	lanSwitchPortEnableStatus
		Integer32,
	lanSwitchPortLinkStatus
		Integer32,
	lanSwitchPortAutonegStatus
		Integer32,
	lanSwitchPortSpeedStatus
		Integer32,
	lanSwitchPortDuplexStatus
		Integer32,
	lanSwitchPortPoEStatus
		Integer32,
	lanSwitchPortPoEVoltage
		Integer32,
	lanSwitchPortPoECurrent
		Integer32
}

lanSwitchPortCAPS OBJECT-TYPE
	SYNTAX     Integer32
	MAX-ACCESS read-only
	STATUS     current
	DESCRIPTION
		"Switch Port Capability Flags bitmask:
		0(0000b) - PoE is NOT Supported,
		1(0001b) - Manual (Passsive) PoE 24V is supported,
		2(0010b) - Auto (Active) PoE 24V is supported,
		4(0100b) - Manual (Passive) PoE 56V is supported,
		8(1000b) - Auto (Active) PoE 56V 802.3af is supported
		Device Allocation: AP, SM"
	::= { lanSwitchPortStatusEntry 1 }

lanSwitchPortEnableStatus OBJECT-TYPE
	SYNTAX     Integer32
	MAX-ACCESS read-only
	STATUS     current
	DESCRIPTION
		"Switch Port Enable
		0 - Disable,
		1 - Enable
		Device Allocation: AP, SM"
	::= { lanSwitchPortStatusEntry 2 }

lanSwitchPortLinkStatus OBJECT-TYPE
	SYNTAX     Integer32
	MAX-ACCESS read-only
	STATUS     current
	DESCRIPTION
		"Switch Port Link Status
		0 - Down,
		1 - Up
		Device Allocation: AP, SM"
	::= { lanSwitchPortStatusEntry 3 }

lanSwitchPortAutonegStatus OBJECT-TYPE
	SYNTAX     Integer32
	MAX-ACCESS read-only
	STATUS     current
	DESCRIPTION
		"Switch Port Autonegotiation
		-1 - No data,
		0  - Disable,
		1  - Enable
		Device Allocation: AP, SM"
	::= { lanSwitchPortStatusEntry 4 }

lanSwitchPortSpeedStatus OBJECT-TYPE
	SYNTAX     Integer32
	MAX-ACCESS read-only
	STATUS     current
	DESCRIPTION
		"Switch Port Speed
		-1   - No data,
		10   - 10 Mb/s,
		100  - 100 Mb/s,
		1000 - 1000 Mb/s
		Device Allocation: AP, SM"
	::= { lanSwitchPortStatusEntry 5 }

lanSwitchPortDuplexStatus OBJECT-TYPE
	SYNTAX     Integer32
	MAX-ACCESS read-only
	STATUS     current
	DESCRIPTION
		"Switch Port Duplex Mode
		-1 - No data,
		0  - Half,
		1  - Full
		Device Allocation: AP, SM"
	::= { lanSwitchPortStatusEntry 6 }

lanSwitchPortPoEStatus OBJECT-TYPE
	SYNTAX     Integer32
	MAX-ACCESS read-only
	STATUS     current
	DESCRIPTION
		"Switch Port PoE Enable
		-1 - Not Supported,
		 0 - Disable,
		 1 - PoE 24V,
		 2 - PoE 24V in Auto Mode,
		 3 - PoE 56V 802.3af,
		 4 - PoE 56V 802.3af in Auto Mode
		Device Allocation: AP, SM"
	::= { lanSwitchPortStatusEntry 7 }

lanSwitchPortPoEVoltage OBJECT-TYPE
	SYNTAX     Integer32
	MAX-ACCESS read-only
	STATUS     current
	DESCRIPTION
		"POE out voltage measured in mV or -1 (voltage is unknown).
		Device Allocation: AP, SM"
	::= { lanSwitchPortStatusEntry 8 }

lanSwitchPortPoECurrent OBJECT-TYPE
	SYNTAX     Integer32
	MAX-ACCESS read-only
	STATUS     current
	DESCRIPTION
		"POE out current measured in mAh or -1 (current is unknown).
		Device Allocation: AP, SM"
	::= { lanSwitchPortStatusEntry 9 }

cambiumWLAN2Status OBJECT-TYPE
	SYNTAX	   Integer32 (0|1|2)
	MAX-ACCESS read-only
	STATUS	   current
	DESCRIPTION
		"Second Radio WLAN Status:
			0 - Down,
			1 - Up
		Device Allocation: AP, SM"
	::= { cambiumLinkStatus 102 }

cambiumIPAliasEntry OBJECT-TYPE
	SYNTAX	   CambiumIPAliasEntry
	MAX-ACCESS not-accessible
	STATUS	   current
	DESCRIPTION
		"IP aliases list table entry.
		Device Allocation: AP, SM."
	INDEX	{ cambiumIPAliasTableIndex }
	::= { cambiumIPAliasTable 1 }

CambiumIPAliasEntry ::= SEQUENCE {
	cambiumIPAliasTableIndex
		Integer32,
	cambiumIPAliasIP
		IpAddress,
	cambiumIPAliasNetmask
		IpAddress
}

cambiumIPAliasTableIndex  OBJECT-TYPE
	SYNTAX	  Integer32 (0..10)
	MAX-ACCESS read-only
	STATUS	   current
	DESCRIPTION
		"IP aliases table index."
	::= { cambiumIPAliasEntry 1 }

cambiumIPAliasIP  OBJECT-TYPE
	SYNTAX	   IpAddress
	MAX-ACCESS read-only
	STATUS	   current
	DESCRIPTION
		"IP alias IP address."
	::= { cambiumIPAliasEntry 2 }

cambiumIPAliasNetmask  OBJECT-TYPE
	SYNTAX	   IpAddress
	MAX-ACCESS read-only
	STATUS	   current
	DESCRIPTION
		"IP alias netmask."
	::= { cambiumIPAliasEntry 3 }

cambiumARPEntry OBJECT-TYPE
	SYNTAX	   CambiumARPEntry
	MAX-ACCESS not-accessible
	STATUS	   current
	DESCRIPTION
		"Neighbour device IP/MAC pair entry"
	INDEX	{ cambiumARPIndex }
	::= { cambiumARPTable 1 }

CambiumARPEntry ::= SEQUENCE {
	cambiumARPIndex
		Integer32,
	cambiumARPMAC
		DisplayString,
	cambiumARPIP
		IpAddress,
	cambiumARPInterface
		DisplayString
}

cambiumARPIndex	 OBJECT-TYPE
	SYNTAX	  Integer32 (0..1024)
	MAX-ACCESS read-only
	STATUS	   current
	DESCRIPTION
		"Index"
	::= { cambiumARPEntry 1 }

cambiumARPMAC  OBJECT-TYPE
	SYNTAX	   DisplayString (SIZE(0|17))
	MAX-ACCESS read-only
	STATUS	   current
	DESCRIPTION
		"Neighbour device MAC Address"
	::= { cambiumARPEntry 2 }

cambiumARPIP  OBJECT-TYPE
	SYNTAX	   IpAddress
	MAX-ACCESS read-only
	STATUS	   current
	DESCRIPTION
		"Neighbour device IP Address"
	::= { cambiumARPEntry 3 }

cambiumARPInterface	 OBJECT-TYPE
	SYNTAX	   DisplayString (SIZE(0|16))
	MAX-ACCESS read-only
	STATUS	   current
	DESCRIPTION
		"Neighbour device Interface"
	::= { cambiumARPEntry 4 }

cambiumStaticRoutesEntry OBJECT-TYPE
	SYNTAX	   CambiumStaticRoutesEntry
	MAX-ACCESS not-accessible
	STATUS	   current
	DESCRIPTION
		"Static Routes Dest/Getway pair entry"
	INDEX	{ cambiumStaticRoutesIndex }
	::= { cambiumStaticRoutesTable 1 }

CambiumStaticRoutesEntry ::= SEQUENCE {
	cambiumStaticRoutesIndex
		Integer32,
	cambiumStaticRoutesDestIP
		IpAddress,
	cambiumStaticRoutesGW
		IpAddress,
	cambiumStaticRoutesNetmask
		IpAddress,
	cambiumStaticRoutesInterface
		DisplayString
}

cambiumStaticRoutesIndex  OBJECT-TYPE
	SYNTAX	  Integer32 (0..32)
	MAX-ACCESS read-only
	STATUS	   current
	DESCRIPTION
		"Index"
	::= { cambiumStaticRoutesEntry 1 }

cambiumStaticRoutesDestIP  OBJECT-TYPE
	SYNTAX	   IpAddress
	MAX-ACCESS read-only
	STATUS	   current
	DESCRIPTION
		"Destination IP"
	::= { cambiumStaticRoutesEntry 2 }

cambiumStaticRoutesGW  OBJECT-TYPE
	SYNTAX	   IpAddress
	MAX-ACCESS read-only
	STATUS	   current
	DESCRIPTION
		"Getway IP"
	::= { cambiumStaticRoutesEntry 3 }

cambiumStaticRoutesNetmask	OBJECT-TYPE
	SYNTAX	   IpAddress
	MAX-ACCESS read-only
	STATUS	   current
	DESCRIPTION
		"Dest IP Netmask"
	::= { cambiumStaticRoutesEntry 4 }

cambiumStaticRoutesInterface  OBJECT-TYPE
	SYNTAX	   DisplayString (SIZE(0|16))
	MAX-ACCESS read-only
	STATUS	   current
	DESCRIPTION
		"Static Routes Interface Name"
	::= { cambiumStaticRoutesEntry 5 }

cambiumStatsForceUpdate OBJECT-TYPE
	SYNTAX	   Integer32 (0|1)
	MAX-ACCESS read-write
	STATUS	   current
	DESCRIPTION
		"Cambium Statistics Update/Reset Action
		Statistic is updated automatically in the background each 15sec
		SNMP-GET on This OID forces update of subsequent Statistics tree
		SNMP-SET on This OID Resets all of the subsequent Statistic
		Device Allocation: AP, SM"
	::= { cambiumPerformanceMonitoring 1 }

cambiumEthRXBytes OBJECT-TYPE
	SYNTAX	   Counter64
	MAX-ACCESS read-only
	STATUS	   current
	DESCRIPTION
		"Total Ethernet RX bytes
		Device Allocation: AP, SM"
	::= { cambiumPerformanceMonitoring 2 }

cambiumEthRXPackets OBJECT-TYPE
	SYNTAX	   Counter64
	MAX-ACCESS read-only
	STATUS	   current
	DESCRIPTION
		"Total Ethernet RX packets
		Device Allocation: AP, SM"
	::= { cambiumPerformanceMonitoring 3 }

cambiumEthRXErrors OBJECT-TYPE
	SYNTAX	   Counter64
	MAX-ACCESS read-only
	STATUS	   current
	DESCRIPTION
		"Total Ethernet RX errors
		Device Allocation: AP, SM"
	::= { cambiumPerformanceMonitoring 4 }

cambiumEthRXDrops OBJECT-TYPE
	SYNTAX	   Counter64
	MAX-ACCESS read-only
	STATUS	   current
	DESCRIPTION
		"Total Ethernet RX drops
		Device Allocation: AP, SM"
	::= { cambiumPerformanceMonitoring 5 }

cambiumEthRXMulticast OBJECT-TYPE
	SYNTAX	   Counter64
	MAX-ACCESS read-only
	STATUS	   current
	DESCRIPTION
		"Total Ethernet RX multicast
		Device Allocation: AP, SM"
	::= { cambiumPerformanceMonitoring 6 }

cambiumEthRXBroadcast OBJECT-TYPE
	SYNTAX	   Counter64
	MAX-ACCESS read-only
	STATUS	   current
	DESCRIPTION
		"Total Ethernet RX broadcast
		Device Allocation: AP, SM"
	::= { cambiumPerformanceMonitoring 7 }

cambiumEthTXBytes OBJECT-TYPE
	SYNTAX	   Counter64
	MAX-ACCESS read-only
	STATUS	   current
	DESCRIPTION
		"Total Ethernet TX bytes
		Device Allocation: AP, SM"
	::= { cambiumPerformanceMonitoring 8 }

cambiumEthTXPackets OBJECT-TYPE
	SYNTAX	   Counter64
	MAX-ACCESS read-only
	STATUS	   current
	DESCRIPTION
		"Total Ethernet TX packets
		Device Allocation: AP, SM"
	::= { cambiumPerformanceMonitoring 9 }

cambiumEthTXErrors OBJECT-TYPE
	SYNTAX	   Counter64
	MAX-ACCESS read-only
	STATUS	   current
	DESCRIPTION
		"Total Ethernet TX errors
		Device Allocation: AP, SM"
	::= { cambiumPerformanceMonitoring 10 }

cambiumEthTXDrops OBJECT-TYPE
	SYNTAX	   Counter64
	MAX-ACCESS read-only
	STATUS	   current
	DESCRIPTION
		"Total Ethernet TX drops
		Device Allocation: AP, SM"
	::= { cambiumPerformanceMonitoring 11 }

cambiumEthTXMulticast OBJECT-TYPE
	SYNTAX	   Counter64
	MAX-ACCESS read-only
	STATUS	   current
	DESCRIPTION
		"Total Ethernet TX multicast
		Device Allocation: AP, SM"
	::= { cambiumPerformanceMonitoring 12 }

cambiumEthTXBroadcast OBJECT-TYPE
	SYNTAX	   Counter64
	MAX-ACCESS read-only
	STATUS	   current
	DESCRIPTION
		"Total Ethernet TX broadcast
		Device Allocation: AP, SM"
	::= { cambiumPerformanceMonitoring 13 }

cambiumAthRXBytes OBJECT-TYPE
	SYNTAX	   Counter64
	MAX-ACCESS read-only
	STATUS	   obsolete
	DESCRIPTION
		"Total Wireless RX bytes
		Device Allocation: AP, SM"
	::= { cambiumPerformanceMonitoring 21 }

cambiumAthRXPackets OBJECT-TYPE
	SYNTAX	   Counter64
	MAX-ACCESS read-only
	STATUS	   obsolete
	DESCRIPTION
		"Total Wireless RX packets
		Device Allocation: AP, SM"
	::= { cambiumPerformanceMonitoring 22 }

cambiumAthRXErrors OBJECT-TYPE
	SYNTAX	   Counter64
	MAX-ACCESS read-only
	STATUS	   obsolete
	DESCRIPTION
		"Total Wireless RX errors
		Device Allocation: AP, SM"
	::= { cambiumPerformanceMonitoring 23 }

cambiumAthRXDrops OBJECT-TYPE
	SYNTAX	   Counter64
	MAX-ACCESS read-only
	STATUS	   obsolete
	DESCRIPTION
		"Total Wireless RX drops
		Device Allocation: AP, SM"
	::= { cambiumPerformanceMonitoring 24 }

cambiumAthRXMulticast OBJECT-TYPE
	SYNTAX	   Counter64
	MAX-ACCESS read-only
	STATUS	   obsolete
	DESCRIPTION
		"Total Wireless RX multicast
		Device Allocation: AP, SM"
	::= { cambiumPerformanceMonitoring 25 }

cambiumAthRXBroadcast OBJECT-TYPE
	SYNTAX	   Counter64
	MAX-ACCESS read-only
	STATUS	   obsolete
	DESCRIPTION
		"Total Wireless RX broadcast
		Device Allocation: AP, SM"
	::= { cambiumPerformanceMonitoring 26 }

cambiumAthTXBytes OBJECT-TYPE
	SYNTAX	   Counter64
	MAX-ACCESS read-only
	STATUS	   obsolete
	DESCRIPTION
		"Total Wireless TX bytes
		Device Allocation: AP, SM"
	::= { cambiumPerformanceMonitoring 27 }

cambiumAthTXPackets OBJECT-TYPE
	SYNTAX	   Counter64
	MAX-ACCESS read-only
	STATUS	   obsolete
	DESCRIPTION
		"Total Wireless TX packets
		Device Allocation: AP, SM"
	::= { cambiumPerformanceMonitoring 28 }

cambiumAthTXErrors OBJECT-TYPE
	SYNTAX	   Counter64
	MAX-ACCESS read-only
	STATUS	   obsolete
	DESCRIPTION
		"Total Wireless TX errors
		Device Allocation: AP, SM"
	::= { cambiumPerformanceMonitoring 29 }

cambiumAthTXDrops OBJECT-TYPE
	SYNTAX	   Counter64
	MAX-ACCESS read-only
	STATUS	   obsolete
	DESCRIPTION
		"Total Wireless TX drops
		Device Allocation: AP, SM"
	::= { cambiumPerformanceMonitoring 30 }

cambiumAthTXMulticast OBJECT-TYPE
	SYNTAX	   Counter64
	MAX-ACCESS read-only
	STATUS	   obsolete
	DESCRIPTION
		"Total Wireless TX multicast
		Device Allocation: AP, SM"
	::= { cambiumPerformanceMonitoring 31 }

cambiumAthTXBroadcast OBJECT-TYPE
	SYNTAX	   Counter64
	MAX-ACCESS read-only
	STATUS	   obsolete
	DESCRIPTION
		"Total Wireless TX broadcast
		Device Allocation: AP, SM"
	::= { cambiumPerformanceMonitoring 32 }

sysNetworkEntryAttempt OBJECT-TYPE
	SYNTAX	   Counter32
	MAX-ACCESS read-only
	STATUS	   current
	DESCRIPTION
		"Number of attempt to enter the AP network
		Device Allocation: AP"
	::= { cambiumPerformanceMonitoring 33 }

sysNetworkEntrySuccess OBJECT-TYPE
	SYNTAX	   Counter32
	MAX-ACCESS read-only
	STATUS	   current
	DESCRIPTION
		"Number of successful network entry into the AP
		Device Allocation: AP"
	::= { cambiumPerformanceMonitoring 34 }

sysNetworkEntryAuthenticationFailure OBJECT-TYPE
	SYNTAX	   Counter32
	MAX-ACCESS read-only
	STATUS	   current
	DESCRIPTION
		"Number of failed network entry into the AP due to
		authentication failure
		Device Allocation: AP"
	::= { cambiumPerformanceMonitoring 35 }

sysDFSDetectedCount OBJECT-TYPE
	SYNTAX	   Counter32
	MAX-ACCESS read-only
	STATUS	   current
	DESCRIPTION
		"Number of DFS detected during channel initialization or during
		service which causes channel remap
		Device Allocation: AP, SM"
	::= { cambiumPerformanceMonitoring 36 }

ulWLanKbitCount OBJECT-TYPE
	SYNTAX	   Counter64
	MAX-ACCESS read-only
	STATUS	   current
	DESCRIPTION
		"Aggregated total Uplink data traffic in kilobits
		Device Allocation: AP, SM"
	::= { cambiumPerformanceMonitoring 37 }

dlWLanKbitCount OBJECT-TYPE
	SYNTAX	   Counter64
	MAX-ACCESS read-only
	STATUS	   current
	DESCRIPTION
		"Aggregated total Downlink data traffic in kilobits
		Device Allocation: AP, SM"
	::= { cambiumPerformanceMonitoring 38 }

ulWLanTotalPacketCount OBJECT-TYPE
	SYNTAX	   Counter64
	MAX-ACCESS read-only
	STATUS	   current
	DESCRIPTION
		"Aggregated number of total Uplink data packet transmitted by
		SM or received by AP
		Device Allocation: AP, SM"
	::= { cambiumPerformanceMonitoring 39 }

muWLanKbitCount OBJECT-TYPE
	SYNTAX	   Counter64
	MAX-ACCESS read-only
	STATUS	   current
	DESCRIPTION
		"MU-MIMO Downlink data traffic in kilobits
		Device Allocation: AP"
	::= { cambiumPerformanceMonitoring 40 }

sysRebootCount OBJECT-TYPE
	SYNTAX	   Integer32
	MAX-ACCESS read-only
	STATUS	   obsolete
	DESCRIPTION
		"Device Reboot Counter
		Device Allocation: AP, SM"
	::= { cambiumPerformanceMonitoring 41 }

dlWLanTotalPacketCount OBJECT-TYPE
	SYNTAX	   Counter64
	MAX-ACCESS read-only
	STATUS	   current
	DESCRIPTION
		"Aggregated number of total Downlink data packet transmitted by
		AP or received by SM
		Device Allocation: AP, SM"
	::= { cambiumPerformanceMonitoring 42 }

ulWLanMultiBroadcastKbitCount OBJECT-TYPE
	SYNTAX	   Counter64
	MAX-ACCESS read-only
	STATUS	   current
	DESCRIPTION
		"Aggregated total Uplink multicast and broadcast data traffic in
		kilobits
		Device Allocation: AP, SM"
	::= { cambiumPerformanceMonitoring 43 }

dlWLanMultiBroadcastKbitCount OBJECT-TYPE
	SYNTAX	   Counter64
	MAX-ACCESS read-only
	STATUS	   current
	DESCRIPTION
		"Aggregated total Downlink multicast and broadcast data traffic
		in kilobits
		Device Allocation: AP, SM"
	::= { cambiumPerformanceMonitoring 44 }

wLanSessionDroppedCount OBJECT-TYPE
	SYNTAX	   Counter32
	MAX-ACCESS read-only
	STATUS	   current
	DESCRIPTION
		"Aggregated number of SM session dropped due to no responses of
		bandwidth request response
		Device Allocation: AP, SM"
	::= { cambiumPerformanceMonitoring 45 }

cambiumTDDStatsPerSTATable OBJECT-TYPE
	SYNTAX	   SEQUENCE OF CambiumTDDStatsPerSTAEntry
	MAX-ACCESS not-accessible
	STATUS	   current
	DESCRIPTION
		"This table contains information relevant to customer TDD Statistics
		for connected SMs:
		- station MAC Address,
		- uplink data traffic in Kbits for a single SM;
		- downlink data traffic in Kbits for a single SM;
		- number of uplink total data packet received at AP for a single SM;
		- number of downlink total data packet transmitted at AP for a single
		  SM;
		- number of uplink data packet dropped due to data integrity error or
		  other RF related packer errors for a single SM;
		- number of downlink data packet dropped due to no-acknowledgement or
		  other RF related packet error for a single SM;
		- number of downlink data packet dropped due to data buffer/queue
		  overflow or other system internal buffer/sending related packet
		  error for a single SM;
		- number of downlink data packet retransmitted due to no-acknowledge
		  for a single SM.
		Device Allocation: AP"
	::= { cambiumPerformanceMonitoring 46 }

cambiumTDDStatsPerSTAEntry OBJECT-TYPE
	SYNTAX	   CambiumTDDStatsPerSTAEntry
	MAX-ACCESS not-accessible
	STATUS	   current
	DESCRIPTION
		"Customer TDD Statistics for particular SM
		 Device Allocation: AP"
	INDEX	{ cambiumTDDStatsPerSTAIndex }
	::= { cambiumTDDStatsPerSTATable 1 }

CambiumTDDStatsPerSTAEntry ::= SEQUENCE {
	cambiumTDDStatsPerSTAIndex				Integer32,
	cambiumTDDStatsListMAC					DisplayString,
	ulWLanPerUserKbitCount					Counter64,
	dlWLanPerUserKbitCount					Counter64,
	ulWLanPerUserTotalPacketCount			Counter64,
	dlWLanPerUserTotalPacketCount			Counter64,
	ulWLanPerUserErrorDroppedPacketCount	Counter64,
	dlWLanPerUserErrorDroppedPacketCount	Counter64,
	dlWLanPerUserCapacityDroppedPacketCount Counter64,
	dlWLanPerUserRetransmitPacketCount		Counter64,
	dlWLanPerUserTxPower					Integer32,
	cambiumTDDStatsIP						IpAddress,
	cambiumTDDStatsDevName					DisplayString,
	dlWLanPerUserRetransmitMsduCount		Counter64
}

cambiumTDDStatsPerSTAIndex OBJECT-TYPE
	SYNTAX	   Integer32 (0..120)
	MAX-ACCESS read-only
	STATUS	   current
	DESCRIPTION
		"Table index"
	::= { cambiumTDDStatsPerSTAEntry 1 }

cambiumTDDStatsListMAC OBJECT-TYPE
	SYNTAX	   DisplayString (SIZE(0|11..17))
	MAX-ACCESS read-only
	STATUS	   current
	DESCRIPTION
		"Connected SM WLAN MAC Address
		Device Allocation: AP"
	::= { cambiumTDDStatsPerSTAEntry 2 }

ulWLanPerUserKbitCount OBJECT-TYPE
	SYNTAX	   Counter64
	MAX-ACCESS read-only
	STATUS	   current
	DESCRIPTION
		"Uplink data traffic in Kbits for a single SM
		Device Allocation: AP"
	::= { cambiumTDDStatsPerSTAEntry 3 }

dlWLanPerUserKbitCount OBJECT-TYPE
	SYNTAX	   Counter64
	MAX-ACCESS read-only
	STATUS	   current
	DESCRIPTION
		"Downlink data traffic in Kbits for a single SM
		Device Allocation: AP"
	::= { cambiumTDDStatsPerSTAEntry 4 }

ulWLanPerUserTotalPacketCount OBJECT-TYPE
	SYNTAX	   Counter64
	MAX-ACCESS read-only
	STATUS	   current
	DESCRIPTION
		"Number of uplink total data packet received at AP for a single SM
		Device Allocation: AP"
	::= { cambiumTDDStatsPerSTAEntry 5 }

dlWLanPerUserTotalPacketCount OBJECT-TYPE
	SYNTAX	   Counter64
	MAX-ACCESS read-only
	STATUS	   current
	DESCRIPTION
		"Number of downlink total data packet transmitted at AP for a single
		SM
		Device Allocation: AP"
	::= { cambiumTDDStatsPerSTAEntry 6 }

ulWLanPerUserErrorDroppedPacketCount OBJECT-TYPE
	SYNTAX	   Counter64
	MAX-ACCESS read-only
	STATUS	   current
	DESCRIPTION
		"Number of uplink data packet dropped due to data integrity error or
		other RF related packer errors for a single SM
		Device Allocation: AP"
	::= { cambiumTDDStatsPerSTAEntry 7 }

dlWLanPerUserErrorDroppedPacketCount OBJECT-TYPE
	SYNTAX	   Counter64
	MAX-ACCESS read-only
	STATUS	   current
	DESCRIPTION
		"Number of downlink data packet dropped due to no-acknowledgement or
		other RF related packet error for a single SM
		Device Allocation: AP"
	::= { cambiumTDDStatsPerSTAEntry 8 }

dlWLanPerUserCapacityDroppedPacketCount OBJECT-TYPE
	SYNTAX	   Counter64
	MAX-ACCESS read-only
	STATUS	   current
	DESCRIPTION
		"Number of downlink data packet dropped due to data buffer/queue
		overflow or other system internal buffer/sending related packet error
		for a single SM
		Device Allocation: AP"
	::= { cambiumTDDStatsPerSTAEntry 9 }

dlWLanPerUserRetransmitPacketCount OBJECT-TYPE
	SYNTAX	   Counter64
	MAX-ACCESS read-only
	STATUS	   current
	DESCRIPTION
		"Number of downlink MPDU retransmitted due to no-acknowledge
		for a single SM
		Device Allocation: AP"
	::= { cambiumTDDStatsPerSTAEntry 10 }

dlWLanPerUserTxPower OBJECT-TYPE
	SYNTAX	   Integer32
	MAX-ACCESS read-only
	STATUS	   current
	DESCRIPTION
		"Downlink TxPower of data packages for a single SM
		Device Allocation: AP"
	::= { cambiumTDDStatsPerSTAEntry 11 }

cambiumTDDStatsIP OBJECT-TYPE
	SYNTAX	   IpAddress
	MAX-ACCESS read-only
	STATUS	   current
	DESCRIPTION
		"IP address of SM
		Device Allocation: AP"
	::= { cambiumTDDStatsPerSTAEntry 12 }

cambiumTDDStatsDevName OBJECT-TYPE
	SYNTAX	   DisplayString (SIZE(0|1..32))
	MAX-ACCESS read-only
	STATUS	   current
	DESCRIPTION
		"Hostname of SM
		Device Allocation: AP"
	::= { cambiumTDDStatsPerSTAEntry 13 }

dlWLanPerUserRetransmitMsduCount OBJECT-TYPE
	SYNTAX	   Counter64
	MAX-ACCESS read-only
	STATUS	   current
	DESCRIPTION
		"Number of downlink data packets (MSDU) retransmitted due to no-acknowledge
		for a single SM
		Device Allocation: AP"
	::= { cambiumTDDStatsPerSTAEntry 14 }

ulWLanErrorDroppedPacketCount OBJECT-TYPE
	SYNTAX	   Counter64
	MAX-ACCESS read-only
	STATUS	   current
	DESCRIPTION
		"Aggregated number of total Uplink data packet dropped due to
		data integrity error or other data packet association or RF
		error in packet
		Device Allocation: AP, SM"
	::= { cambiumPerformanceMonitoring 47 }

dlWLanErrorDroppedPacketCount OBJECT-TYPE
	SYNTAX	   Counter64
	MAX-ACCESS read-only
	STATUS	   current
	DESCRIPTION
		"Aggregated number of total Downlink data packet dropped due to
		data integrity error or other data packet association error in
		packet
		Device Allocation: AP, SM"
	::= { cambiumPerformanceMonitoring 48 }

ulWLanCapacityDroppedPacketCount OBJECT-TYPE
	SYNTAX	   Counter64
	MAX-ACCESS read-only
	STATUS	   current
	DESCRIPTION
		"Aggregated number of total Uplink data packet dropped due to
		WLAN capacity issue in packets
		Device Allocation: AP, SM"
	::= { cambiumPerformanceMonitoring 49 }

dlWLanCapacityDroppedPacketCount OBJECT-TYPE
	SYNTAX	   Counter64
	MAX-ACCESS read-only
	STATUS	   current
	DESCRIPTION
		"Aggregated number of total Downlink data packet dropped due to
		exceed data buffer, over capacity or internal packet package
		sent issues in packet
		Device Allocation: AP, SM"
	::= { cambiumPerformanceMonitoring 50 }

ulWLanTotalAvailableFrameTimePerSecond OBJECT-TYPE
	SYNTAX	   Integer32
	MAX-ACCESS read-only
	STATUS	   current
	DESCRIPTION
		"Aggregated number of total uplink available frame time can be
		scheduled for traffic in micro second for 1 second period
		Device Allocation: AP"
	::= { cambiumPerformanceMonitoring 51 }

dlWLanTotalAvailableFrameTimePerSecond OBJECT-TYPE
	SYNTAX	   Integer32
	MAX-ACCESS read-only
	STATUS	   current
	DESCRIPTION
		"Aggregated number of total downlink available frame time can be
		scheduled for traffic in micro second for 1 second period
		Device Allocation: AP"
	::= { cambiumPerformanceMonitoring 52 }

ulWLanTotalUsedFrameTimePerSecond OBJECT-TYPE
	SYNTAX	   Integer32
	MAX-ACCESS read-only
	STATUS	   current
	DESCRIPTION
		"Aggregated number of uplink frame time schedule to be used in
		microsecond for 1 second period
		Device Allocation: AP"
	::= { cambiumPerformanceMonitoring 53 }

dlWLanTotalUsedFrameTimePerSecond OBJECT-TYPE
	SYNTAX	   Integer32
	MAX-ACCESS read-only
	STATUS	   current
	DESCRIPTION
		"Aggregated number of downlink frame time scheduled to be used
		per frame for 1 second period
		Device Allocation: AP"
	::= { cambiumPerformanceMonitoring 54 }

ulWLanTotalOverheadFrameTimePerSecond OBJECT-TYPE
	SYNTAX	   Integer32
	MAX-ACCESS read-only
	STATUS	   current
	DESCRIPTION
		"Aggregated number of uplink frame time is used for overhead
		(preamble and inter-frame gap) in microsecond for 1 second
		period
		Device Allocation: AP"
	::= { cambiumPerformanceMonitoring 55 }

dlWLanTotalOverheadFrameTimePerSecond OBJECT-TYPE
	SYNTAX	   Integer32
	MAX-ACCESS read-only
	STATUS	   current
	DESCRIPTION
		"Aggregated number of downlink frame time is used for overhead
		(preamble ans inter-frame gap) per frame for 1 second period
		Device Allocation: AP"
	::= { cambiumPerformanceMonitoring 56 }

cambiumMCSTable OBJECT-TYPE
	SYNTAX	   SEQUENCE OF CambiumMCSEntry
	MAX-ACCESS not-accessible
	STATUS	   obsolete
	DESCRIPTION
		"This table contains information relevant to customer TDD Statistics
		for MCS RX and TX rates:
		- MCS number (MCSxx);
		- Aggregated number of uplink frame time used for MCSxx in
		  microsecond for 1 second period;
		- Aggregated number of downlink frame time used for MCSxx in
		  microsecond for 1 second period.
		Device Allocation: AP"
	::= { cambiumPerformanceMonitoring 57 }

cambiumMCSEntry OBJECT-TYPE
	SYNTAX	   CambiumMCSEntry
	MAX-ACCESS not-accessible
	STATUS	   obsolete
	DESCRIPTION
		"MCS table
		Device Allocation: AP"
	INDEX	{ cambiumMCSIndex }
	::= { cambiumMCSTable 1 }

CambiumMCSEntry ::= SEQUENCE {
	cambiumMCSIndex					Integer32,
	cambiumMCSNumber				DisplayString,
	ulWLanMCSUsedFrameTimePerSecond Counter32,
	dlWLanMCSUsedFrameTimePerSecond Counter32
}

cambiumMCSIndex OBJECT-TYPE
	SYNTAX	   Integer32 (0..24)
	MAX-ACCESS read-only
	STATUS	   obsolete
	DESCRIPTION
		"MCS index
		Device Allocation: AP"
	::= { cambiumMCSEntry 1 }

cambiumMCSNumber OBJECT-TYPE
	SYNTAX	   DisplayString
	MAX-ACCESS read-only
	STATUS	   obsolete
	DESCRIPTION
		"MCS number (MCSxx)
		Device Allocation: AP"
	::= { cambiumMCSEntry 2 }

ulWLanMCSUsedFrameTimePerSecond OBJECT-TYPE
	SYNTAX	   Counter32
	MAX-ACCESS read-only
	STATUS	   obsolete
	DESCRIPTION
		"Aggregated number of uplink frame time used for MCSxx in
			microsecond for 1 second period
		Device Allocation: AP"
	::= { cambiumMCSEntry 3 }

dlWLanMCSUsedFrameTimePerSecond OBJECT-TYPE
	SYNTAX	   Counter32
	MAX-ACCESS read-only
	STATUS	   obsolete
	DESCRIPTION
		"Aggregated number of downlink frame time used for MCSxx in
			microsecond for 1 second period
		Device Allocation: AP"
	::= { cambiumMCSEntry 4 }

ulWLanRetransPacketCount OBJECT-TYPE
	SYNTAX	   Counter64
	MAX-ACCESS read-only
	STATUS	   current
	DESCRIPTION
		"Aggregated number of total Uplink data packet retransmitted due
		to no-acknowledgement.
		Device Allocation: SM"
	::= { cambiumPerformanceMonitoring 58 }

dlWLanRetransPacketCount OBJECT-TYPE
	SYNTAX	   Counter64
	MAX-ACCESS read-only
	STATUS	   current
	DESCRIPTION
		"Aggregated number of total Downlink data packet retransmitted
		due to no-acknowledgement
		Device Allocation: AP"
	::= { cambiumPerformanceMonitoring 59 }

ulWLanBroadcastPacketCount OBJECT-TYPE
	SYNTAX	   Counter64
	MAX-ACCESS read-only
	STATUS	   current
	DESCRIPTION
		"Aggregated total Uplink broadcast packet counter
		Device Allocation: AP, SM"
	::= { cambiumPerformanceMonitoring 60 }

dlWLanBroadcastPacketCount OBJECT-TYPE
	SYNTAX	   Counter64
	MAX-ACCESS read-only
	STATUS	   current
	DESCRIPTION
		"Aggregated total Downlink broadcast packet counter
		Device Allocation: AP, SM"
	::= { cambiumPerformanceMonitoring 61 }

ulWLanMulticastPacketCount OBJECT-TYPE
	SYNTAX	   Counter64
	MAX-ACCESS read-only
	STATUS	   current
	DESCRIPTION
		"Aggregated total Uplink multicast packet counter
		Device Allocation: AP, SM"
	::= { cambiumPerformanceMonitoring 62 }

dlWLanMulticastPacketCount OBJECT-TYPE
	SYNTAX	   Counter64
	MAX-ACCESS read-only
	STATUS	   current
	DESCRIPTION
		"Aggregated total Downlink multicast packet counter
		Device Allocation: AP, SM"
	::= { cambiumPerformanceMonitoring 63 }

sysCPUUsage OBJECT-TYPE
	SYNTAX	   Counter32
	MAX-ACCESS read-only
	STATUS	   current
	DESCRIPTION
		"CPU Usage, measuring up to 0.1%
		Range: 0..1000
		Device Allocation: AP, SM"
	::= { cambiumPerformanceMonitoring 64 }

rxEtherLanKbitCount OBJECT-TYPE
	SYNTAX	   Counter64
	MAX-ACCESS read-only
	STATUS	   current
	DESCRIPTION
		"Total Ethernet RX bytes
		Device Allocation: AP, SM"
	::= { cambiumPerformanceMonitoring 65 }

rxEtherLanTotalPacketCount OBJECT-TYPE
	SYNTAX	   Counter64
	MAX-ACCESS read-only
	STATUS	   current
	DESCRIPTION
		"Total Ethernet RX packets
		Device Allocation: AP, SM"
	::= { cambiumPerformanceMonitoring 66 }

rxEtherLanErrorPacketCount OBJECT-TYPE
	SYNTAX	   Counter64
	MAX-ACCESS read-only
	STATUS	   current
	DESCRIPTION
		"Total Ethernet RX errors
		Device Allocation: AP, SM"
	::= { cambiumPerformanceMonitoring 67 }

rxEtherLanDroppedPacketCount OBJECT-TYPE
	SYNTAX	   Counter64
	MAX-ACCESS read-only
	STATUS	   current
	DESCRIPTION
		"Total Ethernet RX drops
		Device Allocation: AP, SM"
	::= { cambiumPerformanceMonitoring 68 }

rxEtherLanMulticastPacketCount OBJECT-TYPE
	SYNTAX	   Counter64
	MAX-ACCESS read-only
	STATUS	   current
	DESCRIPTION
		"Total Ethernet RX multicast
		Device Allocation: AP, SM"
	::= { cambiumPerformanceMonitoring 69 }

rxEtherLanBroadcastPacketCount OBJECT-TYPE
	SYNTAX	   Counter64
	MAX-ACCESS read-only
	STATUS	   current
	DESCRIPTION
		"Total Ethernet RX broadcast
		Device Allocation: AP, SM"
	::= { cambiumPerformanceMonitoring 70 }

rxEtherLanMultiBroadcastKbitCount OBJECT-TYPE
	SYNTAX	   Counter64
	MAX-ACCESS read-only
	STATUS	   current
	DESCRIPTION
		"Aggregated total Ethernet RX multicast and broadcast data traffic
		Device Allocation: AP, SM"
	::= { cambiumPerformanceMonitoring 71 }

txEtherLanKbitCount OBJECT-TYPE
	SYNTAX	   Counter64
	MAX-ACCESS read-only
	STATUS	   current
	DESCRIPTION
		"Total Ethernet TX bytes
		Device Allocation: AP, SM"
	::= { cambiumPerformanceMonitoring 72 }

txEtherLanTotalPacketCount OBJECT-TYPE
	SYNTAX	   Counter64
	MAX-ACCESS read-only
	STATUS	   current
	DESCRIPTION
		"Total Ethernet TX packets
		Device Allocation: AP, SM"
	::= { cambiumPerformanceMonitoring 73 }

txEtherLanErrorPacketCount OBJECT-TYPE
	SYNTAX	   Counter64
	MAX-ACCESS read-only
	STATUS	   current
	DESCRIPTION
		"Total Ethernet TX errors
		Device Allocation: AP, SM"
	::= { cambiumPerformanceMonitoring 74 }

txEtherLanDroppedPacketCount OBJECT-TYPE
	SYNTAX	   Counter64
	MAX-ACCESS read-only
	STATUS	   current
	DESCRIPTION
		"Total Ethernet TX drops
		Device Allocation: AP, SM"
	::= { cambiumPerformanceMonitoring 75 }

txEtherLanMulticastPacketCount OBJECT-TYPE
	SYNTAX	   Counter64
	MAX-ACCESS read-only
	STATUS	   current
	DESCRIPTION
		"Total Ethernet TX multicast
		Device Allocation: AP, SM"
	::= { cambiumPerformanceMonitoring 76 }

txEtherLanBroadcastPacketCount OBJECT-TYPE
	SYNTAX	   Counter64
	MAX-ACCESS read-only
	STATUS	   current
	DESCRIPTION
		"Total Ethernet TX broadcast
		Device Allocation: AP, SM"
	::= { cambiumPerformanceMonitoring 77 }

txEtherLanMultiBroadcastKbitCount OBJECT-TYPE
	SYNTAX	   Counter64
	MAX-ACCESS read-only
	STATUS	   current
	DESCRIPTION
		"Aggregated total Ethernet TX multicast and broadcast data traffic
		Device Allocation: AP, SM"
	::= { cambiumPerformanceMonitoring 78 }

cambiumStatsResetTimer OBJECT-TYPE
	SYNTAX	   TimeTicks
	MAX-ACCESS read-only
	STATUS	   current
	DESCRIPTION
		"Status time to indicate when is the last time stats are reset
		Device Allocation: AP, SM"
	::= { cambiumPerformanceMonitoring 79 }

ulWLanMCS00Packets OBJECT-TYPE
	SYNTAX	   Counter64
	MAX-ACCESS read-only
	STATUS	   current
	DESCRIPTION
		"Aggregated number of uplink packet received for HT MCS00
		Device Allocation: AP"
	::= { cambiumPerformanceMonitoring 80 }

ulWLanMCS01Packets OBJECT-TYPE
	SYNTAX	   Counter64
	MAX-ACCESS read-only
	STATUS	   current
	DESCRIPTION
		"Aggregated number of uplink packet received for HT MCS01
		Device Allocation: AP"
	::= { cambiumPerformanceMonitoring 81 }

ulWLanMCS02Packets OBJECT-TYPE
	SYNTAX	   Counter64
	MAX-ACCESS read-only
	STATUS	   current
	DESCRIPTION
		"Aggregated number of uplink packet received for HT MCS02
		Device Allocation: AP"
	::= { cambiumPerformanceMonitoring 82 }

ulWLanMCS03Packets OBJECT-TYPE
	SYNTAX	   Counter64
	MAX-ACCESS read-only
	STATUS	   current
	DESCRIPTION
		"Aggregated number of uplink packet received for HT MCS03
		Device Allocation: AP"
	::= { cambiumPerformanceMonitoring 83 }

ulWLanMCS04Packets OBJECT-TYPE
	SYNTAX	   Counter64
	MAX-ACCESS read-only
	STATUS	   current
	DESCRIPTION
		"Aggregated number of uplink packet received for HT MCS04
		Device Allocation: AP"
	::= { cambiumPerformanceMonitoring 84 }

ulWLanMCS05Packets OBJECT-TYPE
	SYNTAX	   Counter64
	MAX-ACCESS read-only
	STATUS	   current
	DESCRIPTION
		"Aggregated number of uplink packet received for HT MCS05
		Device Allocation: AP"
	::= { cambiumPerformanceMonitoring 85 }

ulWLanMCS06Packets OBJECT-TYPE
	SYNTAX	   Counter64
	MAX-ACCESS read-only
	STATUS	   current
	DESCRIPTION
		"Aggregated number of uplink packet received for HT MCS06
		Device Allocation: AP"
	::= { cambiumPerformanceMonitoring 86 }

ulWLanMCS07Packets OBJECT-TYPE
	SYNTAX	   Counter64
	MAX-ACCESS read-only
	STATUS	   current
	DESCRIPTION
		"Aggregated number of uplink packet received for HT MCS07
		Device Allocation: AP"
	::= { cambiumPerformanceMonitoring 87 }

ulWLanMCS08Packets OBJECT-TYPE
	SYNTAX	   Counter64
	MAX-ACCESS read-only
	STATUS	   current
	DESCRIPTION
		"Aggregated number of uplink packet received for HT MCS08
		Device Allocation: AP"
	::= { cambiumPerformanceMonitoring 88 }

ulWLanMCS09Packets OBJECT-TYPE
	SYNTAX	   Counter64
	MAX-ACCESS read-only
	STATUS	   current
	DESCRIPTION
		"Aggregated number of uplink packet received for HT MCS09
		Device Allocation: AP"
	::= { cambiumPerformanceMonitoring 89 }

ulWLanMCS10Packets OBJECT-TYPE
	SYNTAX	   Counter64
	MAX-ACCESS read-only
	STATUS	   current
	DESCRIPTION
		"Aggregated number of uplink packet received for HT MCS10
		Device Allocation: AP"
	::= { cambiumPerformanceMonitoring 90 }

ulWLanMCS11Packets OBJECT-TYPE
	SYNTAX	   Counter64
	MAX-ACCESS read-only
	STATUS	   current
	DESCRIPTION
		"Aggregated number of uplink packet received for HT MCS11
		Device Allocation: AP"
	::= { cambiumPerformanceMonitoring 91 }

ulWLanMCS12Packets OBJECT-TYPE
	SYNTAX	   Counter64
	MAX-ACCESS read-only
	STATUS	   current
	DESCRIPTION
		"Aggregated number of uplink packet received for HT MCS12
		Device Allocation: AP"
	::= { cambiumPerformanceMonitoring 92 }

ulWLanMCS13Packets OBJECT-TYPE
	SYNTAX	   Counter64
	MAX-ACCESS read-only
	STATUS	   current
	DESCRIPTION
		"Aggregated number of uplink packet received for HT MCS13
		Device Allocation: AP"
	::= { cambiumPerformanceMonitoring 93 }

ulWLanMCS14Packets OBJECT-TYPE
	SYNTAX	   Counter64
	MAX-ACCESS read-only
	STATUS	   current
	DESCRIPTION
		"Aggregated number of uplink packet received for HT MCS14
		Device Allocation: AP"
	::= { cambiumPerformanceMonitoring 94 }

ulWLanMCS15Packets OBJECT-TYPE
	SYNTAX	   Counter64
	MAX-ACCESS read-only
	STATUS	   current
	DESCRIPTION
		"Aggregated number of uplink packet received for HT MCS15
		Device Allocation: AP"
	::= { cambiumPerformanceMonitoring 95 }

dlWLanMCS00Packets OBJECT-TYPE
	SYNTAX	   Counter64
	MAX-ACCESS read-only
	STATUS	   current
	DESCRIPTION
		"Aggregated number of downlink packet received for HT MCS00
		Device Allocation: AP"
	::= { cambiumPerformanceMonitoring 96 }

dlWLanMCS01Packets OBJECT-TYPE
	SYNTAX	   Counter64
	MAX-ACCESS read-only
	STATUS	   current
	DESCRIPTION
		"Aggregated number of downlink packet received for HT MCS01
		Device Allocation: AP"
	::= { cambiumPerformanceMonitoring 97 }

dlWLanMCS02Packets OBJECT-TYPE
	SYNTAX	   Counter64
	MAX-ACCESS read-only
	STATUS	   current
	DESCRIPTION
		"Aggregated number of downlink packet received for HT MCS02
		Device Allocation: AP"
	::= { cambiumPerformanceMonitoring 98 }

dlWLanMCS03Packets OBJECT-TYPE
	SYNTAX	   Counter64
	MAX-ACCESS read-only
	STATUS	   current
	DESCRIPTION
		"Aggregated number of downlink packet received for HT MCS03
		Device Allocation: AP"
	::= { cambiumPerformanceMonitoring 99 }

dlWLanMCS04Packets OBJECT-TYPE
	SYNTAX	   Counter64
	MAX-ACCESS read-only
	STATUS	   current
	DESCRIPTION
		"Aggregated number of downlink packet received for HT MCS04
		Device Allocation: AP"
	::= { cambiumPerformanceMonitoring 100 }

dlWLanMCS05Packets OBJECT-TYPE
	SYNTAX	   Counter64
	MAX-ACCESS read-only
	STATUS	   current
	DESCRIPTION
		"Aggregated number of downlink packet received for HT MCS05
		Device Allocation: AP"
	::= { cambiumPerformanceMonitoring 101 }

dlWLanMCS06Packets OBJECT-TYPE
	SYNTAX	   Counter64
	MAX-ACCESS read-only
	STATUS	   current
	DESCRIPTION
		"Aggregated number of downlink packet received for HT MCS06
		Device Allocation: AP"
	::= { cambiumPerformanceMonitoring 102 }

dlWLanMCS07Packets OBJECT-TYPE
	SYNTAX	   Counter64
	MAX-ACCESS read-only
	STATUS	   current
	DESCRIPTION
		"Aggregated number of downlink packet received for HT MCS07
		Device Allocation: AP"
	::= { cambiumPerformanceMonitoring 103 }

dlWLanMCS08Packets OBJECT-TYPE
	SYNTAX	   Counter64
	MAX-ACCESS read-only
	STATUS	   current
	DESCRIPTION
		"Aggregated number of downlink packet received for HT MCS08
		Device Allocation: AP"
	::= { cambiumPerformanceMonitoring 104 }

dlWLanMCS09Packets OBJECT-TYPE
	SYNTAX	   Counter64
	MAX-ACCESS read-only
	STATUS	   current
	DESCRIPTION
		"Aggregated number of downlink packet received for HT MCS09
		Device Allocation: AP"
	::= { cambiumPerformanceMonitoring 105 }

dlWLanMCS10Packets OBJECT-TYPE
	SYNTAX	   Counter64
	MAX-ACCESS read-only
	STATUS	   current
	DESCRIPTION
		"Aggregated number of downlink packet received for HT MCS10
		Device Allocation: AP"
	::= { cambiumPerformanceMonitoring 106 }

dlWLanMCS11Packets OBJECT-TYPE
	SYNTAX	   Counter64
	MAX-ACCESS read-only
	STATUS	   current
	DESCRIPTION
		"Aggregated number of downlink packet received for HT MCS11
		Device Allocation: AP"
	::= { cambiumPerformanceMonitoring 107 }

dlWLanMCS12Packets OBJECT-TYPE
	SYNTAX	   Counter64
	MAX-ACCESS read-only
	STATUS	   current
	DESCRIPTION
		"Aggregated number of downlink packet received for HT MCS12
		Device Allocation: AP"
	::= { cambiumPerformanceMonitoring 108 }

dlWLanMCS13Packets OBJECT-TYPE
	SYNTAX	   Counter64
	MAX-ACCESS read-only
	STATUS	   current
	DESCRIPTION
		"Aggregated number of downlink packet received for HT MCS13
		Device Allocation: AP"
	::= { cambiumPerformanceMonitoring 109 }

dlWLanMCS14Packets OBJECT-TYPE
	SYNTAX	   Counter64
	MAX-ACCESS read-only
	STATUS	   current
	DESCRIPTION
		"Aggregated number of downlink packet received for HT MCS14
		Device Allocation: AP"
	::= { cambiumPerformanceMonitoring 110 }

dlWLanMCS15Packets OBJECT-TYPE
	SYNTAX	   Counter64
	MAX-ACCESS read-only
	STATUS	   current
	DESCRIPTION
		"Aggregated number of downlink packet received for HT MCS15
		Device Allocation: AP"
	::= { cambiumPerformanceMonitoring 111 }

ulWLanTotalAvailableFrameTimePercentage OBJECT-TYPE
	SYNTAX     Integer32
	MAX-ACCESS read-only
	STATUS     current
	DESCRIPTION
		"Aggregated uplink frame 10X percentage time
		Range = [1..1000] 0.1% = 1; 100% = 1000
		Device Allocation: AP"
	::= { cambiumPerformanceMonitoring 112 }

dlWLanTotalAvailableFrameTimePercentage OBJECT-TYPE
	SYNTAX     Integer32
	MAX-ACCESS read-only
	STATUS     current
	DESCRIPTION
		"Aggregated downlink frame 10X percentage time
		Range = [1..1000] 0.1% = 1; 100% = 1000
		Device Allocation: AP"
	::= { cambiumPerformanceMonitoring 113 }
ePMP2000MapMissCounter OBJECT-TYPE
	SYNTAX	   Counter32
	MAX-ACCESS read-only
	STATUS	   current
	DESCRIPTION
		"ePMP2000/ePMP3000: Map Miss counter
		Device Allocation: AP"
	::= { cambiumPerformanceMonitoring 115 }

ePMP2000PatternSkipCounter OBJECT-TYPE
	SYNTAX	   Counter32
	MAX-ACCESS read-only
	STATUS	   current
	DESCRIPTION
		"ePMP2000/ePMP3000: Pattern skip counter
		Device Allocation: AP"
	::= { cambiumPerformanceMonitoring 116 }

ePMP2000ErrorsSmartAntennaInterface OBJECT-TYPE
	SYNTAX	   Counter32
	MAX-ACCESS read-only
	STATUS	   current
	DESCRIPTION
		"ePMP2000/ePMP3000: Number of errors seen on the SmartAntenna interface (handshake errors)
		Device Allocation: AP"
	::= { cambiumPerformanceMonitoring 117 }

classificationVoiceQueuePutPacketCount OBJECT-TYPE
	SYNTAX	   Counter32
	MAX-ACCESS read-only
	STATUS	   current
	DESCRIPTION
		"Total count of put packets to VOICE queue
		Device Allocation: AP, SM"
	::= { cambiumPerformanceMonitoring 118 }

classificationVoiceQueueGetPacketCount OBJECT-TYPE
	SYNTAX	   Counter32
	MAX-ACCESS read-only
	STATUS	   current
	DESCRIPTION
		"Total count of get packets from VOICE queue
		Device Allocation: AP, SM"
	::= { cambiumPerformanceMonitoring 119 }

classificationVoiceQueueDropPacketCount OBJECT-TYPE
	SYNTAX	   Counter32
	MAX-ACCESS read-only
	STATUS	   current
	DESCRIPTION
		"Total count of dropped packets from VOICE queue
		Device Allocation: AP, SM"
	::= { cambiumPerformanceMonitoring 120 }

classificationHighQueuePutPacketCount OBJECT-TYPE
	SYNTAX	   Counter32
	MAX-ACCESS read-only
	STATUS	   current
	DESCRIPTION
		"Total count of put packets to HIGH queue
		Device Allocation: AP, SM"
	::= { cambiumPerformanceMonitoring 121 }

classificationHighQueueGetPacketCount OBJECT-TYPE
	SYNTAX	   Counter32
	MAX-ACCESS read-only
	STATUS	   current
	DESCRIPTION
		"Total count of get packets from HIGH queue
		Device Allocation: AP, SM"
	::= { cambiumPerformanceMonitoring 122 }

classificationHighQueueDropPacketCount OBJECT-TYPE
	SYNTAX	   Counter32
	MAX-ACCESS read-only
	STATUS	   current
	DESCRIPTION
		"Total count of dropped packets from HIGH queue
		Device Allocation: AP, SM"
	::= { cambiumPerformanceMonitoring 123 }

classificationLowQueuePutPacketCount OBJECT-TYPE
	SYNTAX	   Counter32
	MAX-ACCESS read-only
	STATUS	   current
	DESCRIPTION
		"Total count of put packets to LOW queue
		Device Allocation: AP, SM"
	::= { cambiumPerformanceMonitoring 124 }

classificationLowQueueGetPacketCount OBJECT-TYPE
	SYNTAX	   Counter32
	MAX-ACCESS read-only
	STATUS	   current
	DESCRIPTION
		"Total count of get packets from LOW queue
		Device Allocation: AP, SM"
	::= { cambiumPerformanceMonitoring 125 }

classificationLowQueueDropPacketCount OBJECT-TYPE
	SYNTAX	   Counter32
	MAX-ACCESS read-only
	STATUS	   current
	DESCRIPTION
		"Total count of dropped packets from LOW queue
		Device Allocation: AP, SM"
	::= { cambiumPerformanceMonitoring 126 }

classificationTotalQueuePutPacketCount OBJECT-TYPE
	SYNTAX	   Counter32
	MAX-ACCESS read-only
	STATUS	   current
	DESCRIPTION
		"Total count of put packets to all queues
		Device Allocation: AP, SM"
	::= { cambiumPerformanceMonitoring 127 }

classificationTotalQueueGetPacketCount OBJECT-TYPE
	SYNTAX	   Counter32
	MAX-ACCESS read-only
	STATUS	   current
	DESCRIPTION
		"Total count of get packets from all queues
		Device Allocation: AP, SM"
	::= { cambiumPerformanceMonitoring 128 }

classificationTotalQueueDropPacketCount OBJECT-TYPE
	SYNTAX	   Counter32
	MAX-ACCESS read-only
	STATUS	   current
	DESCRIPTION
		"Total count of dropped packets from all queues
		Device Allocation: AP, SM"
	::= { cambiumPerformanceMonitoring 129 }

ulWLanVHTMCS0SSPackets OBJECT-TYPE
	SYNTAX	   Counter64
	MAX-ACCESS read-only
	STATUS	   current
	DESCRIPTION
		"Aggregated number of uplink packet received for VHT MCS0 Single Stream
		Device Allocation: AP"
	::= { cambiumPerformanceMonitoring 130 }

ulWLanVHTMCS1SSPackets OBJECT-TYPE
	SYNTAX	   Counter64
	MAX-ACCESS read-only
	STATUS	   current
	DESCRIPTION
		"Aggregated number of uplink packet received for VHT MCS1 Single Stream
		Device Allocation: AP"
	::= { cambiumPerformanceMonitoring 131 }

ulWLanVHTMCS2SSPackets OBJECT-TYPE
	SYNTAX	   Counter64
	MAX-ACCESS read-only
	STATUS	   current
	DESCRIPTION
		"Aggregated number of uplink packet received for VHT MCS2 Single Stream
		Device Allocation: AP"
	::= { cambiumPerformanceMonitoring 132 }

ulWLanVHTMCS3SSPackets OBJECT-TYPE
	SYNTAX	   Counter64
	MAX-ACCESS read-only
	STATUS	   current
	DESCRIPTION
		"Aggregated number of uplink packet received for VHT MCS3 Single Stream
		Device Allocation: AP"
	::= { cambiumPerformanceMonitoring 133 }

ulWLanVHTMCS4SSPackets OBJECT-TYPE
	SYNTAX	   Counter64
	MAX-ACCESS read-only
	STATUS	   current
	DESCRIPTION
		"Aggregated number of uplink packet received for VHT MCS4 Single Stream
		Device Allocation: AP"
	::= { cambiumPerformanceMonitoring 134 }

ulWLanVHTMCS5SSPackets OBJECT-TYPE
	SYNTAX	   Counter64
	MAX-ACCESS read-only
	STATUS	   current
	DESCRIPTION
		"Aggregated number of uplink packet received for VHT MCS5 Single Stream
		Device Allocation: AP"
	::= { cambiumPerformanceMonitoring 135 }

ulWLanVHTMCS6SSPackets OBJECT-TYPE
	SYNTAX	   Counter64
	MAX-ACCESS read-only
	STATUS	   current
	DESCRIPTION
		"Aggregated number of uplink packet received for VHT MCS6 Single Stream
		Device Allocation: AP"
	::= { cambiumPerformanceMonitoring 136 }

ulWLanVHTMCS7SSPackets OBJECT-TYPE
	SYNTAX	   Counter64
	MAX-ACCESS read-only
	STATUS	   current
	DESCRIPTION
		"Aggregated number of uplink packet received for VHT MCS7 Single Stream
		Device Allocation: AP"
	::= { cambiumPerformanceMonitoring 137 }


ulWLanVHTMCS8SSPackets OBJECT-TYPE
	SYNTAX	   Counter64
	MAX-ACCESS read-only
	STATUS	   current
	DESCRIPTION
		"Aggregated number of uplink packet received for VHT MCS8 Single Stream
		Device Allocation: AP"
	::= { cambiumPerformanceMonitoring 138 }

ulWLanVHTMCS9SSPackets OBJECT-TYPE
	SYNTAX	   Counter64
	MAX-ACCESS read-only
	STATUS	   current
	DESCRIPTION
		"Aggregated number of uplink packet received for VHT MCS9 Single Stream
		Device Allocation: AP"
	::= { cambiumPerformanceMonitoring 139 }

ulWLanVHTMCS0DSPackets OBJECT-TYPE
	SYNTAX	   Counter64
	MAX-ACCESS read-only
	STATUS	   current
	DESCRIPTION
		"Aggregated number of uplink packet received for VHT MCS0 Dual Stream
		Device Allocation: AP"
	::= { cambiumPerformanceMonitoring 140 }

ulWLanVHTMCS1DSPackets OBJECT-TYPE
	SYNTAX	   Counter64
	MAX-ACCESS read-only
	STATUS	   current
	DESCRIPTION
		"Aggregated number of uplink packet received for VHT MCS1 Dual Stream
		Device Allocation: AP"
	::= { cambiumPerformanceMonitoring 141 }

ulWLanVHTMCS2DSPackets OBJECT-TYPE
	SYNTAX	   Counter64
	MAX-ACCESS read-only
	STATUS	   current
	DESCRIPTION
		"Aggregated number of uplink packet received for VHT MCS2 Dual Stream
		Device Allocation: AP"
	::= { cambiumPerformanceMonitoring 142 }

ulWLanVHTMCS3DSPackets OBJECT-TYPE
	SYNTAX	   Counter64
	MAX-ACCESS read-only
	STATUS	   current
	DESCRIPTION
		"Aggregated number of uplink packet received for VHT MCS3 Dual Stream
		Device Allocation: AP"
	::= { cambiumPerformanceMonitoring 143 }

ulWLanVHTMCS4DSPackets OBJECT-TYPE
	SYNTAX	   Counter64
	MAX-ACCESS read-only
	STATUS	   current
	DESCRIPTION
		"Aggregated number of uplink packet received for VHT MCS4 Dual Stream
		Device Allocation: AP"
	::= { cambiumPerformanceMonitoring 144 }

ulWLanVHTMCS5DSPackets OBJECT-TYPE
	SYNTAX	   Counter64
	MAX-ACCESS read-only
	STATUS	   current
	DESCRIPTION
		"Aggregated number of uplink packet received for VHT MCS5 Dual Stream
		Device Allocation: AP"
	::= { cambiumPerformanceMonitoring 145 }

ulWLanVHTMCS6DSPackets OBJECT-TYPE
	SYNTAX	   Counter64
	MAX-ACCESS read-only
	STATUS	   current
	DESCRIPTION
		"Aggregated number of uplink packet received for VHT MCS6 Dual Stream
		Device Allocation: AP"
	::= { cambiumPerformanceMonitoring 146 }

ulWLanVHTMCS7DSPackets OBJECT-TYPE
	SYNTAX	   Counter64
	MAX-ACCESS read-only
	STATUS	   current
	DESCRIPTION
		"Aggregated number of uplink packet received for VHT MCS7 Dual Stream
		Device Allocation: AP"
	::= { cambiumPerformanceMonitoring 147 }


ulWLanVHTMCS8DSPackets OBJECT-TYPE
	SYNTAX	   Counter64
	MAX-ACCESS read-only
	STATUS	   current
	DESCRIPTION
		"Aggregated number of uplink packet received for VHT MCS8 Dual Stream
		Device Allocation: AP"
	::= { cambiumPerformanceMonitoring 148 }

ulWLanVHTMCS9DSPackets OBJECT-TYPE
	SYNTAX	   Counter64
	MAX-ACCESS read-only
	STATUS	   current
	DESCRIPTION
		"Aggregated number of uplink packet received for VHT MCS9 Dual Stream
		Device Allocation: AP"
	::= { cambiumPerformanceMonitoring 149 }

dlWLanVHTMCS0SSPackets OBJECT-TYPE
	SYNTAX	   Counter64
	MAX-ACCESS read-only
	STATUS	   current
	DESCRIPTION
		"Aggregated number of downlink packet received for VHT MCS0 Single Stream
		Device Allocation: AP"
	::= { cambiumPerformanceMonitoring 150 }

dlWLanVHTMCS1SSPackets OBJECT-TYPE
	SYNTAX	   Counter64
	MAX-ACCESS read-only
	STATUS	   current
	DESCRIPTION
		"Aggregated number of downlink packet received for VHT MCS1 Single Stream
		Device Allocation: AP"
	::= { cambiumPerformanceMonitoring 151 }

dlWLanVHTMCS2SSPackets OBJECT-TYPE
	SYNTAX	   Counter64
	MAX-ACCESS read-only
	STATUS	   current
	DESCRIPTION
		"Aggregated number of downlink packet received for VHT MCS2 Single Stream
		Device Allocation: AP"
	::= { cambiumPerformanceMonitoring 152 }

dlWLanVHTMCS3SSPackets OBJECT-TYPE
	SYNTAX	   Counter64
	MAX-ACCESS read-only
	STATUS	   current
	DESCRIPTION
		"Aggregated number of downlink packet received for VHT MCS3 Single Stream
		Device Allocation: AP"
	::= { cambiumPerformanceMonitoring 153 }

dlWLanVHTMCS4SSPackets OBJECT-TYPE
	SYNTAX	   Counter64
	MAX-ACCESS read-only
	STATUS	   current
	DESCRIPTION
		"Aggregated number of downlink packet received for VHT MCS4 Single Stream
		Device Allocation: AP"
	::= { cambiumPerformanceMonitoring 154 }

dlWLanVHTMCS5SSPackets OBJECT-TYPE
	SYNTAX	   Counter64
	MAX-ACCESS read-only
	STATUS	   current
	DESCRIPTION
		"Aggregated number of downlink packet received for VHT MCS5 Single Stream
		Device Allocation: AP"
	::= { cambiumPerformanceMonitoring 155 }

dlWLanVHTMCS6SSPackets OBJECT-TYPE
	SYNTAX	   Counter64
	MAX-ACCESS read-only
	STATUS	   current
	DESCRIPTION
		"Aggregated number of downlink packet received for VHT MCS6 Single Stream
		Device Allocation: AP"
	::= { cambiumPerformanceMonitoring 156 }

dlWLanVHTMCS7SSPackets OBJECT-TYPE
	SYNTAX	   Counter64
	MAX-ACCESS read-only
	STATUS	   current
	DESCRIPTION
		"Aggregated number of downlink packet received for VHT MCS7 Single Stream
		Device Allocation: AP"
	::= { cambiumPerformanceMonitoring 157 }


dlWLanVHTMCS8SSPackets OBJECT-TYPE
	SYNTAX	   Counter64
	MAX-ACCESS read-only
	STATUS	   current
	DESCRIPTION
		"Aggregated number of downlink packet received for VHT MCS8 Single Stream
		Device Allocation: AP"
	::= { cambiumPerformanceMonitoring 158 }

dlWLanVHTMCS9SSPackets OBJECT-TYPE
	SYNTAX	   Counter64
	MAX-ACCESS read-only
	STATUS	   current
	DESCRIPTION
		"Aggregated number of downlink packet received for VHT MCS9 Single Stream
		Device Allocation: AP"
	::= { cambiumPerformanceMonitoring 159 }

dlWLanVHTMCS0DSPackets OBJECT-TYPE
	SYNTAX	   Counter64
	MAX-ACCESS read-only
	STATUS	   current
	DESCRIPTION
		"Aggregated number of downlink packet received for VHT MCS0 Dual Stream
		Device Allocation: AP"
	::= { cambiumPerformanceMonitoring 160 }

dlWLanVHTMCS1DSPackets OBJECT-TYPE
	SYNTAX	   Counter64
	MAX-ACCESS read-only
	STATUS	   current
	DESCRIPTION
		"Aggregated number of downlink packet received for VHT MCS1 Dual Stream
		Device Allocation: AP"
	::= { cambiumPerformanceMonitoring 161 }

dlWLanVHTMCS2DSPackets OBJECT-TYPE
	SYNTAX	   Counter64
	MAX-ACCESS read-only
	STATUS	   current
	DESCRIPTION
		"Aggregated number of downlink packet received for VHT MCS2 Dual Stream
		Device Allocation: AP"
	::= { cambiumPerformanceMonitoring 162 }

dlWLanVHTMCS3DSPackets OBJECT-TYPE
	SYNTAX	   Counter64
	MAX-ACCESS read-only
	STATUS	   current
	DESCRIPTION
		"Aggregated number of downlink packet received for VHT MCS3 Dual Stream
		Device Allocation: AP"
	::= { cambiumPerformanceMonitoring 163 }

dlWLanVHTMCS4DSPackets OBJECT-TYPE
	SYNTAX	   Counter64
	MAX-ACCESS read-only
	STATUS	   current
	DESCRIPTION
		"Aggregated number of downlink packet received for VHT MCS4 Dual Stream
		Device Allocation: AP"
	::= { cambiumPerformanceMonitoring 164 }

dlWLanVHTMCS5DSPackets OBJECT-TYPE
	SYNTAX	   Counter64
	MAX-ACCESS read-only
	STATUS	   current
	DESCRIPTION
		"Aggregated number of downlink packet received for VHT MCS5 Dual Stream
		Device Allocation: AP"
	::= { cambiumPerformanceMonitoring 165 }

dlWLanVHTMCS6DSPackets OBJECT-TYPE
	SYNTAX	   Counter64
	MAX-ACCESS read-only
	STATUS	   current
	DESCRIPTION
		"Aggregated number of downlink packet received for VHT MCS6 Dual Stream
		Device Allocation: AP"
	::= { cambiumPerformanceMonitoring 166 }

dlWLanVHTMCS7DSPackets OBJECT-TYPE
	SYNTAX	   Counter64
	MAX-ACCESS read-only
	STATUS	   current
	DESCRIPTION
		"Aggregated number of downlink packet received for VHT MCS7 Dual Stream
		Device Allocation: AP"
	::= { cambiumPerformanceMonitoring 167 }

dlWLanVHTMCS8DSPackets OBJECT-TYPE
	SYNTAX	   Counter64
	MAX-ACCESS read-only
	STATUS	   current
	DESCRIPTION
		"Aggregated number of downlink packet received for VHT MCS8 Dual Stream
		Device Allocation: AP"
	::= { cambiumPerformanceMonitoring 168 }

dlWLanVHTMCS9DSPackets OBJECT-TYPE
	SYNTAX	   Counter64
	MAX-ACCESS read-only
	STATUS	   current
	DESCRIPTION
		"Aggregated number of downlink packet received for VHT MCS9 Dual Stream
		Device Allocation: AP"
	::= { cambiumPerformanceMonitoring 169 }

wLanSNRDeviation00Cnt OBJECT-TYPE
	SYNTAX	   Counter64
	MAX-ACCESS read-only
	STATUS	   current
	DESCRIPTION
		"Number of deviations from average SNR with absolute value 00
		Device Allocation: AP, SM"
	::= { cambiumPerformanceMonitoring 170 }

wLanSNRDeviation01Cnt OBJECT-TYPE
	SYNTAX	   Counter64
	MAX-ACCESS read-only
	STATUS	   current
	DESCRIPTION
		"Number of deviations from average SNR with absolute value 01
		Device Allocation: AP, SM"
	::= { cambiumPerformanceMonitoring 171 }

wLanSNRDeviation02Cnt OBJECT-TYPE
	SYNTAX	   Counter64
	MAX-ACCESS read-only
	STATUS	   current
	DESCRIPTION
		"Number of deviations from average SNR with absolute value 02
		Device Allocation: AP, SM"
	::= { cambiumPerformanceMonitoring 172 }

wLanSNRDeviation03Cnt OBJECT-TYPE
	SYNTAX	   Counter64
	MAX-ACCESS read-only
	STATUS	   current
	DESCRIPTION
		"Number of deviations from average SNR with absolute value 03
		Device Allocation: AP, SM"
	::= { cambiumPerformanceMonitoring 173 }

wLanSNRDeviation04Cnt OBJECT-TYPE
	SYNTAX	   Counter64
	MAX-ACCESS read-only
	STATUS	   current
	DESCRIPTION
		"Number of deviations from average SNR with absolute value 04
		Device Allocation: AP, SM"
	::= { cambiumPerformanceMonitoring 174 }

wLanSNRDeviation05Cnt OBJECT-TYPE
	SYNTAX	   Counter64
	MAX-ACCESS read-only
	STATUS	   current
	DESCRIPTION
		"Number of deviations from average SNR with absolute value 05
		Device Allocation: AP, SM"
	::= { cambiumPerformanceMonitoring 175 }

wLanSNRDeviation06Cnt OBJECT-TYPE
	SYNTAX	   Counter64
	MAX-ACCESS read-only
	STATUS	   current
	DESCRIPTION
		"Number of deviations from average SNR with absolute value 06
		Device Allocation: AP, SM"
	::= { cambiumPerformanceMonitoring 176 }

wLanSNRDeviation07Cnt OBJECT-TYPE
	SYNTAX	   Counter64
	MAX-ACCESS read-only
	STATUS	   current
	DESCRIPTION
		"Number of deviations from average SNR with absolute value 07
		Device Allocation: AP, SM"
	::= { cambiumPerformanceMonitoring 177 }

wLanSNRDeviation08Cnt OBJECT-TYPE
	SYNTAX	   Counter64
	MAX-ACCESS read-only
	STATUS	   current
	DESCRIPTION
		"Number of deviations from average SNR with absolute value 08
		Device Allocation: AP, SM"
	::= { cambiumPerformanceMonitoring 178 }

wLanSNRDeviation09Cnt OBJECT-TYPE
	SYNTAX	   Counter64
	MAX-ACCESS read-only
	STATUS	   current
	DESCRIPTION
		"Number of deviations from average SNR with absolute value 09
		Device Allocation: AP, SM"
	::= { cambiumPerformanceMonitoring 179 }

wLanSNRDeviation10Cnt OBJECT-TYPE
	SYNTAX	   Counter64
	MAX-ACCESS read-only
	STATUS	   current
	DESCRIPTION
		"Number of deviations from average SNR with absolute value 10
		Device Allocation: AP, SM"
	::= { cambiumPerformanceMonitoring 180 }

wLanSNRDeviation11Cnt OBJECT-TYPE
	SYNTAX	   Counter64
	MAX-ACCESS read-only
	STATUS	   current
	DESCRIPTION
		"Number of deviations from average SNR with absolute value 11
		Device Allocation: AP, SM"
	::= { cambiumPerformanceMonitoring 181 }

wLanSNRDeviation12Cnt OBJECT-TYPE
	SYNTAX	   Counter64
	MAX-ACCESS read-only
	STATUS	   current
	DESCRIPTION
		"Number of deviations from average SNR with absolute value 12
		Device Allocation: AP, SM"
	::= { cambiumPerformanceMonitoring 182 }

wLanSNRDeviation13Cnt OBJECT-TYPE
	SYNTAX	   Counter64
	MAX-ACCESS read-only
	STATUS	   current
	DESCRIPTION
		"Number of deviations from average SNR with absolute value 13
		Device Allocation: AP, SM"
	::= { cambiumPerformanceMonitoring 183 }

wLanSNRDeviation14Cnt OBJECT-TYPE
	SYNTAX	   Counter64
	MAX-ACCESS read-only
	STATUS	   current
	DESCRIPTION
		"Number of deviations from average SNR with absolute value 14
		Device Allocation: AP, SM"
	::= { cambiumPerformanceMonitoring 184 }

wLanSNRDeviation15Cnt OBJECT-TYPE
	SYNTAX	   Counter64
	MAX-ACCESS read-only
	STATUS	   current
	DESCRIPTION
		"Number of deviations from average SNR with absolute value 15
		Device Allocation: AP, SM"
	::= { cambiumPerformanceMonitoring 185 }

wLanSNRDeviation16Cnt OBJECT-TYPE
	SYNTAX	   Counter64
	MAX-ACCESS read-only
	STATUS	   current
	DESCRIPTION
		"Number of deviations from average SNR with absolute value 16
		Device Allocation: AP, SM"
	::= { cambiumPerformanceMonitoring 186 }

wLanSNRDeviation17Cnt OBJECT-TYPE
	SYNTAX	   Counter64
	MAX-ACCESS read-only
	STATUS	   current
	DESCRIPTION
		"Number of deviations from average SNR with absolute value 17
		Device Allocation: AP, SM"
	::= { cambiumPerformanceMonitoring 187 }

wLanSNRDeviation18Cnt OBJECT-TYPE
	SYNTAX	   Counter64
	MAX-ACCESS read-only
	STATUS	   current
	DESCRIPTION
		"Number of deviations from average SNR with absolute value 18
		Device Allocation: AP, SM"
	::= { cambiumPerformanceMonitoring 188 }

wLanSNRDeviation19Cnt OBJECT-TYPE
	SYNTAX	   Counter64
	MAX-ACCESS read-only
	STATUS	   current
	DESCRIPTION
		"Number of deviations from average SNR with absolute value 19
		Device Allocation: AP, SM"
	::= { cambiumPerformanceMonitoring 189 }

wlanHEMCSPackets		OBJECT IDENTIFIER ::= { cambiumPerformanceMonitoring 190 }
dlWlanHEMCSPackets		OBJECT IDENTIFIER ::= { wlanHEMCSPackets 1 }
ulWlanHEMCSPackets		OBJECT IDENTIFIER ::= { wlanHEMCSPackets 2 }

lanSwitchPortPerfTable OBJECT-TYPE
	SYNTAX SEQUENCE OF LanSwitchPortPerfEntry
	MAX-ACCESS not-accessible
	STATUS     current
	DESCRIPTION
		"Switch performance monitoring"
	::= { cambiumPerformanceMonitoring 191 }

dlWLanRetransMpduPacketCount OBJECT-TYPE
	SYNTAX	   Counter64
	MAX-ACCESS read-only
	STATUS	   current
	DESCRIPTION
		"Aggregated number of total Downlink MPDU retransmitted
		due to no-acknowledgement
		Device Allocation: AP"
	::= { cambiumPerformanceMonitoring 192 }

ulWLanRetransMpduPacketCount OBJECT-TYPE
	SYNTAX	   Counter64
	MAX-ACCESS read-only
	STATUS	   current
	DESCRIPTION
		"Aggregated number of total Uplink MPDU retransmitted
		due to no-acknowledgement
		Device Allocation: AP"
	::= { cambiumPerformanceMonitoring 193 }

lanSwitchPortPerfEntry OBJECT-TYPE
	SYNTAX     LanSwitchPortPerfEntry
	MAX-ACCESS not-accessible
	STATUS     current
	DESCRIPTION
		"Switch performance monitoring
		Device Allocation: AP, SM"
	INDEX	{ lanSwitchPortsNum }
	::= { lanSwitchPortPerfTable 1 }

LanSwitchPortPerfEntry ::= SEQUENCE {
	rxSwitchPortKBCount
		Counter64,
	rxSwitchPortTotalPacketCount
		Counter64,
	rxSwitchPortErrorPacketCount
		Counter64,
	rxSwitchPortUnicastPacketCount
		Counter64,
	rxSwitchPortMulticastPacketCount
		Counter64,
	rxSwitchPortBroadcastPacketCount
		Counter64,
	txSwitchPortKBCount
		Counter64,
	txSwitchPortTotalPacketCount
		Counter64,
	txSwitchPortErrorPacketCount
		Counter64,
	txSwitchPortUnicastPacketCount
		Counter64,
	txSwitchPortMulticastPacketCount
		Counter64,
	txSwitchPortBroadcastPacketCount
		Counter64
}

rxSwitchPortKBCount OBJECT-TYPE
	SYNTAX     Counter64
	MAX-ACCESS read-only
	STATUS     current
	DESCRIPTION
		"Total port RX kilobytes
		Device Allocation: AP, SM"
	::= { lanSwitchPortPerfEntry 1 }

rxSwitchPortTotalPacketCount OBJECT-TYPE
	SYNTAX     Counter64
	MAX-ACCESS read-only
	STATUS     current
	DESCRIPTION
		"Total port RX packets
		Device Allocation: AP, SM"
	::= { lanSwitchPortPerfEntry 2 }

rxSwitchPortErrorPacketCount OBJECT-TYPE
	SYNTAX     Counter64
	MAX-ACCESS read-only
	STATUS     current
	DESCRIPTION
		"Total port RX errors
		Device Allocation: AP, SM"
	::= { lanSwitchPortPerfEntry 3 }

rxSwitchPortUnicastPacketCount OBJECT-TYPE
	SYNTAX     Counter64
	MAX-ACCESS read-only
	STATUS     current
	DESCRIPTION
		"Total port RX unicast packets
		Device Allocation: AP, SM"
	::= { lanSwitchPortPerfEntry 4 }

rxSwitchPortMulticastPacketCount OBJECT-TYPE
	SYNTAX     Counter64
	MAX-ACCESS read-only
	STATUS     current
	DESCRIPTION
		"Total port RX multicast packets
		Device Allocation: AP, SM"
	::= { lanSwitchPortPerfEntry 5 }

rxSwitchPortBroadcastPacketCount OBJECT-TYPE
	SYNTAX     Counter64
	MAX-ACCESS read-only
	STATUS     current
	DESCRIPTION
		"Total port RX broadcast packets
		Device Allocation: AP, SM"
	::= { lanSwitchPortPerfEntry 6 }

txSwitchPortKBCount OBJECT-TYPE
	SYNTAX     Counter64
	MAX-ACCESS read-only
	STATUS     current
	DESCRIPTION
		"Total port TX kilobytes
		Device Allocation: AP, SM"
	::= { lanSwitchPortPerfEntry 7 }

txSwitchPortTotalPacketCount OBJECT-TYPE
	SYNTAX     Counter64
	MAX-ACCESS read-only
	STATUS     current
	DESCRIPTION
		"Total port TX packets
		Device Allocation: AP, SM"
	::= { lanSwitchPortPerfEntry 8 }

txSwitchPortErrorPacketCount OBJECT-TYPE
	SYNTAX     Counter64
	MAX-ACCESS read-only
	STATUS     current
	DESCRIPTION
		"Total port TX errors
		Device Allocation: AP, SM"
	::= { lanSwitchPortPerfEntry 9 }

txSwitchPortUnicastPacketCount OBJECT-TYPE
	SYNTAX     Counter64
	MAX-ACCESS read-only
	STATUS     current
	DESCRIPTION
		"Total port TX unicast packets
		Device Allocation: AP, SM"
	::= { lanSwitchPortPerfEntry 10 }


txSwitchPortMulticastPacketCount OBJECT-TYPE
	SYNTAX     Counter64
	MAX-ACCESS read-only
	STATUS     current
	DESCRIPTION
		"Total port TX multicast packets
		Device Allocation: AP, SM"
	::= { lanSwitchPortPerfEntry 11 }

txSwitchPortBroadcastPacketCount OBJECT-TYPE
	SYNTAX     Counter64
	MAX-ACCESS read-only
	STATUS     current
	DESCRIPTION
		"Total port TX broadcast packets
		Device Allocation: AP, SM"
	::= { lanSwitchPortPerfEntry 12 }

dlWLanHEMCS0S1Packets OBJECT-TYPE
	SYNTAX		Counter64
	MAX-ACCESS read-only
	STATUS		current
	DESCRIPTION
		"Aggregated number of downlink packet received for HE MCS0 1 Spatial Stream
		Device Allocation: AP"
	::= { dlWlanHEMCSPackets 1 }

dlWLanHEMCS1S1Packets OBJECT-TYPE
	SYNTAX		Counter64
	MAX-ACCESS read-only
	STATUS		current
	DESCRIPTION
		"Aggregated number of downlink packet received for HE MCS1 1 Spatial Stream
		Device Allocation: AP"
	::= { dlWlanHEMCSPackets 2 }

dlWLanHEMCS2S1Packets OBJECT-TYPE
	SYNTAX		Counter64
	MAX-ACCESS read-only
	STATUS		current
	DESCRIPTION
		"Aggregated number of downlink packet received for HE MCS2 1 Spatial Stream
		Device Allocation: AP"
	::= { dlWlanHEMCSPackets 3 }

dlWLanHEMCS3S1Packets OBJECT-TYPE
	SYNTAX		Counter64
	MAX-ACCESS read-only
	STATUS		current
	DESCRIPTION
		"Aggregated number of downlink packet received for HE MCS3 1 Spatial Stream
		Device Allocation: AP"
	::= { dlWlanHEMCSPackets 4 }

dlWLanHEMCS4S1Packets OBJECT-TYPE
	SYNTAX		Counter64
	MAX-ACCESS read-only
	STATUS		current
	DESCRIPTION
		"Aggregated number of downlink packet received for HE MCS4 1 Spatial Stream
		Device Allocation: AP"
	::= { dlWlanHEMCSPackets 5 }

dlWLanHEMCS5S1Packets OBJECT-TYPE
	SYNTAX		Counter64
	MAX-ACCESS read-only
	STATUS		current
	DESCRIPTION
		"Aggregated number of downlink packet received for HE MCS5 1 Spatial Stream
		Device Allocation: AP"
	::= { dlWlanHEMCSPackets 6 }

dlWLanHEMCS6S1Packets OBJECT-TYPE
	SYNTAX		Counter64
	MAX-ACCESS read-only
	STATUS		current
	DESCRIPTION
		"Aggregated number of downlink packet received for HE MCS6 1 Spatial Stream
		Device Allocation: AP"
	::= { dlWlanHEMCSPackets 7 }

dlWLanHEMCS7S1Packets OBJECT-TYPE
	SYNTAX		Counter64
	MAX-ACCESS read-only
	STATUS		current
	DESCRIPTION
		"Aggregated number of downlink packet received for HE MCS7 1 Spatial Stream
		Device Allocation: AP"
	::= { dlWlanHEMCSPackets 8 }

dlWLanHEMCS8S1Packets OBJECT-TYPE
	SYNTAX		Counter64
	MAX-ACCESS read-only
	STATUS		current
	DESCRIPTION
		"Aggregated number of downlink packet received for HE MCS8 1 Spatial Stream
		Device Allocation: AP"
	::= { dlWlanHEMCSPackets 9 }

dlWLanHEMCS9S1Packets OBJECT-TYPE
	SYNTAX		Counter64
	MAX-ACCESS read-only
	STATUS		current
	DESCRIPTION
		"Aggregated number of downlink packet received for HE MCS9 1 Spatial Stream
		Device Allocation: AP"
	::= { dlWlanHEMCSPackets 10 }

dlWLanHEMCS10S1Packets OBJECT-TYPE
	SYNTAX		Counter64
	MAX-ACCESS read-only
	STATUS		current
	DESCRIPTION
		"Aggregated number of downlink packet received for HE MCS10 1 Spatial Stream
		Device Allocation: AP"
	::= { dlWlanHEMCSPackets 11 }

dlWLanHEMCS11S1Packets OBJECT-TYPE
	SYNTAX		Counter64
	MAX-ACCESS read-only
	STATUS		current
	DESCRIPTION
		"Aggregated number of downlink packet received for HE MCS11 1 Spatial Stream
		Device Allocation: AP"
	::= { dlWlanHEMCSPackets 12 }

dlWLanHEMCS0S2Packets OBJECT-TYPE
	SYNTAX		Counter64
	MAX-ACCESS read-only
	STATUS		current
	DESCRIPTION
		"Aggregated number of downlink packet received for HE MCS0 2 Spatial Streams
		Device Allocation: AP"
	::= { dlWlanHEMCSPackets 13 }

dlWLanHEMCS1S2Packets OBJECT-TYPE
	SYNTAX		Counter64
	MAX-ACCESS read-only
	STATUS		current
	DESCRIPTION
		"Aggregated number of downlink packet received for HE MCS1 2 Spatial Streams
		Device Allocation: AP"
	::= { dlWlanHEMCSPackets 14 }

dlWLanHEMCS2S2Packets OBJECT-TYPE
	SYNTAX		Counter64
	MAX-ACCESS read-only
	STATUS		current
	DESCRIPTION
		"Aggregated number of downlink packet received for HE MCS2 2 Spatial Streams
		Device Allocation: AP"
	::= { dlWlanHEMCSPackets 15 }

dlWLanHEMCS3S2Packets OBJECT-TYPE
	SYNTAX		Counter64
	MAX-ACCESS read-only
	STATUS		current
	DESCRIPTION
		"Aggregated number of downlink packet received for HE MCS3 2 Spatial Streams
		Device Allocation: AP"
	::= { dlWlanHEMCSPackets 16 }

dlWLanHEMCS4S2Packets OBJECT-TYPE
	SYNTAX		Counter64
	MAX-ACCESS read-only
	STATUS		current
	DESCRIPTION
		"Aggregated number of downlink packet received for HE MCS4 2 Spatial Streams
		Device Allocation: AP"
	::= { dlWlanHEMCSPackets 17 }

dlWLanHEMCS5S2Packets OBJECT-TYPE
	SYNTAX		Counter64
	MAX-ACCESS read-only
	STATUS		current
	DESCRIPTION
		"Aggregated number of downlink packet received for HE MCS5 2 Spatial Streams
		Device Allocation: AP"
	::= { dlWlanHEMCSPackets 18 }

dlWLanHEMCS6S2Packets OBJECT-TYPE
	SYNTAX		Counter64
	MAX-ACCESS read-only
	STATUS		current
	DESCRIPTION
		"Aggregated number of downlink packet received for HE MCS6 2 Spatial Streams
		Device Allocation: AP"
	::= { dlWlanHEMCSPackets 19 }

dlWLanHEMCS7S2Packets OBJECT-TYPE
	SYNTAX		Counter64
	MAX-ACCESS read-only
	STATUS		current
	DESCRIPTION
		"Aggregated number of downlink packet received for HE MCS7 2 Spatial Streams
		Device Allocation: AP"
	::= { dlWlanHEMCSPackets 20 }

dlWLanHEMCS8S2Packets OBJECT-TYPE
	SYNTAX		Counter64
	MAX-ACCESS read-only
	STATUS		current
	DESCRIPTION
		"Aggregated number of downlink packet received for HE MCS8 2 Spatial Streams
		Device Allocation: AP"
	::= { dlWlanHEMCSPackets 21 }

dlWLanHEMCS9S2Packets OBJECT-TYPE
	SYNTAX		Counter64
	MAX-ACCESS read-only
	STATUS		current
	DESCRIPTION
		"Aggregated number of downlink packet received for HE MCS9 2 Spatial Streams
		Device Allocation: AP"
	::= { dlWlanHEMCSPackets 22 }

dlWLanHEMCS10S2Packets OBJECT-TYPE
	SYNTAX		Counter64
	MAX-ACCESS read-only
	STATUS		current
	DESCRIPTION
		"Aggregated number of downlink packet received for HE MCS10 2 Spatial Streams
		Device Allocation: AP"
	::= { dlWlanHEMCSPackets 23 }

dlWLanHEMCS11S2Packets OBJECT-TYPE
	SYNTAX		Counter64
	MAX-ACCESS read-only
	STATUS		current
	DESCRIPTION
		"Aggregated number of downlink packet received for HE MCS11 2 Spatial Streams
		Device Allocation: AP"
	::= { dlWlanHEMCSPackets 24 }

dlWLanHEMCS0S3Packets OBJECT-TYPE
	SYNTAX		Counter64
	MAX-ACCESS read-only
	STATUS		current
	DESCRIPTION
		"Aggregated number of downlink packet received for HE MCS0 3 Spatial Streams
		Device Allocation: AP"
	::= { dlWlanHEMCSPackets 25 }

dlWLanHEMCS1S3Packets OBJECT-TYPE
	SYNTAX		Counter64
	MAX-ACCESS read-only
	STATUS		current
	DESCRIPTION
		"Aggregated number of downlink packet received for HE MCS1 3 Spatial Streams
		Device Allocation: AP"
	::= { dlWlanHEMCSPackets 26 }

dlWLanHEMCS2S3Packets OBJECT-TYPE
	SYNTAX		Counter64
	MAX-ACCESS read-only
	STATUS		current
	DESCRIPTION
		"Aggregated number of downlink packet received for HE MCS2 3 Spatial Streams
		Device Allocation: AP"
	::= { dlWlanHEMCSPackets 27 }

dlWLanHEMCS3S3Packets OBJECT-TYPE
	SYNTAX		Counter64
	MAX-ACCESS read-only
	STATUS		current
	DESCRIPTION
		"Aggregated number of downlink packet received for HE MCS3 3 Spatial Streams
		Device Allocation: AP"
	::= { dlWlanHEMCSPackets 28 }

dlWLanHEMCS4S3Packets OBJECT-TYPE
	SYNTAX		Counter64
	MAX-ACCESS read-only
	STATUS		current
	DESCRIPTION
		"Aggregated number of downlink packet received for HE MCS4 3 Spatial Streams
		Device Allocation: AP"
	::= { dlWlanHEMCSPackets 29 }

dlWLanHEMCS5S3Packets OBJECT-TYPE
	SYNTAX		Counter64
	MAX-ACCESS read-only
	STATUS		current
	DESCRIPTION
		"Aggregated number of downlink packet received for HE MCS5 3 Spatial Streams
		Device Allocation: AP"
	::= { dlWlanHEMCSPackets 30 }

dlWLanHEMCS6S3Packets OBJECT-TYPE
	SYNTAX		Counter64
	MAX-ACCESS read-only
	STATUS		current
	DESCRIPTION
		"Aggregated number of downlink packet received for HE MCS6 3 Spatial Streams
		Device Allocation: AP"
	::= { dlWlanHEMCSPackets 31 }

dlWLanHEMCS7S3Packets OBJECT-TYPE
	SYNTAX		Counter64
	MAX-ACCESS read-only
	STATUS		current
	DESCRIPTION
		"Aggregated number of downlink packet received for HE MCS7 3 Spatial Streams
		Device Allocation: AP"
	::= { dlWlanHEMCSPackets 32 }

dlWLanHEMCS8S3Packets OBJECT-TYPE
	SYNTAX		Counter64
	MAX-ACCESS read-only
	STATUS		current
	DESCRIPTION
		"Aggregated number of downlink packet received for HE MCS8 3 Spatial Streams
		Device Allocation: AP"
	::= { dlWlanHEMCSPackets 33 }

dlWLanHEMCS9S3Packets OBJECT-TYPE
	SYNTAX		Counter64
	MAX-ACCESS read-only
	STATUS		current
	DESCRIPTION
		"Aggregated number of downlink packet received for HE MCS9 3 Spatial Streams
		Device Allocation: AP"
	::= { dlWlanHEMCSPackets 34 }

dlWLanHEMCS10S3Packets OBJECT-TYPE
	SYNTAX		Counter64
	MAX-ACCESS read-only
	STATUS		current
	DESCRIPTION
		"Aggregated number of downlink packet received for HE MCS10 3 Spatial Streams
		Device Allocation: AP"
	::= { dlWlanHEMCSPackets 35 }

dlWLanHEMCS11S3Packets OBJECT-TYPE
	SYNTAX		Counter64
	MAX-ACCESS read-only
	STATUS		current
	DESCRIPTION
		"Aggregated number of downlink packet received for HE MCS11 3 Spatial Streams
		Device Allocation: AP"
	::= { dlWlanHEMCSPackets 36 }

dlWLanHEMCS0S4Packets OBJECT-TYPE
	SYNTAX		Counter64
	MAX-ACCESS read-only
	STATUS		current
	DESCRIPTION
		"Aggregated number of downlink packet received for HE MCS0 4 Spatial Streams
		Device Allocation: AP"
	::= { dlWlanHEMCSPackets 37 }

dlWLanHEMCS1S4Packets OBJECT-TYPE
	SYNTAX		Counter64
	MAX-ACCESS read-only
	STATUS		current
	DESCRIPTION
		"Aggregated number of downlink packet received for HE MCS1 4 Spatial Streams
		Device Allocation: AP"
	::= { dlWlanHEMCSPackets 38 }

dlWLanHEMCS2S4Packets OBJECT-TYPE
	SYNTAX		Counter64
	MAX-ACCESS read-only
	STATUS		current
	DESCRIPTION
		"Aggregated number of downlink packet received for HE MCS2 4 Spatial Streams
		Device Allocation: AP"
	::= { dlWlanHEMCSPackets 39 }

dlWLanHEMCS3S4Packets OBJECT-TYPE
	SYNTAX		Counter64
	MAX-ACCESS read-only
	STATUS		current
	DESCRIPTION
		"Aggregated number of downlink packet received for HE MCS3 4 Spatial Streams
		Device Allocation: AP"
	::= { dlWlanHEMCSPackets 40 }

dlWLanHEMCS4S4Packets OBJECT-TYPE
	SYNTAX		Counter64
	MAX-ACCESS read-only
	STATUS		current
	DESCRIPTION
		"Aggregated number of downlink packet received for HE MCS4 4 Spatial Streams
		Device Allocation: AP"
	::= { dlWlanHEMCSPackets 41 }

dlWLanHEMCS5S4Packets OBJECT-TYPE
	SYNTAX		Counter64
	MAX-ACCESS read-only
	STATUS		current
	DESCRIPTION
		"Aggregated number of downlink packet received for HE MCS5 4 Spatial Streams
		Device Allocation: AP"
	::= { dlWlanHEMCSPackets 42 }

dlWLanHEMCS6S4Packets OBJECT-TYPE
	SYNTAX		Counter64
	MAX-ACCESS read-only
	STATUS		current
	DESCRIPTION
		"Aggregated number of downlink packet received for HE MCS6 4 Spatial Streams
		Device Allocation: AP"
	::= { dlWlanHEMCSPackets 43 }

dlWLanHEMCS7S4Packets OBJECT-TYPE
	SYNTAX		Counter64
	MAX-ACCESS read-only
	STATUS		current
	DESCRIPTION
		"Aggregated number of downlink packet received for HE MCS7 4 Spatial Streams
		Device Allocation: AP"
	::= { dlWlanHEMCSPackets 44 }

dlWLanHEMCS8S4Packets OBJECT-TYPE
	SYNTAX		Counter64
	MAX-ACCESS read-only
	STATUS		current
	DESCRIPTION
		"Aggregated number of downlink packet received for HE MCS8 4 Spatial Streams
		Device Allocation: AP"
	::= { dlWlanHEMCSPackets 45 }

dlWLanHEMCS9S4Packets OBJECT-TYPE
	SYNTAX		Counter64
	MAX-ACCESS read-only
	STATUS		current
	DESCRIPTION
		"Aggregated number of downlink packet received for HE MCS9 4 Spatial Streams
		Device Allocation: AP"
	::= { dlWlanHEMCSPackets 46 }

dlWLanHEMCS10S4Packets OBJECT-TYPE
	SYNTAX		Counter64
	MAX-ACCESS read-only
	STATUS		current
	DESCRIPTION
		"Aggregated number of downlink packet received for HE MCS10 4 Spatial Streams
		Device Allocation: AP"
	::= { dlWlanHEMCSPackets 47 }

dlWLanHEMCS11S4Packets OBJECT-TYPE
	SYNTAX		Counter64
	MAX-ACCESS read-only
	STATUS		current
	DESCRIPTION
		"Aggregated number of downlink packet received for HE MCS11 4 Spatial Streams
		Device Allocation: AP"
	::= { dlWlanHEMCSPackets 48 }

dlWLanHEMCS0S5Packets OBJECT-TYPE
	SYNTAX		Counter64
	MAX-ACCESS read-only
	STATUS		current
	DESCRIPTION
		"Aggregated number of downlink packet received for HE MCS0 5 Spatial Streams
		Device Allocation: AP"
	::= { dlWlanHEMCSPackets 49 }

dlWLanHEMCS1S5Packets OBJECT-TYPE
	SYNTAX		Counter64
	MAX-ACCESS read-only
	STATUS		current
	DESCRIPTION
		"Aggregated number of downlink packet received for HE MCS1 5 Spatial Streams
		Device Allocation: AP"
	::= { dlWlanHEMCSPackets 50 }

dlWLanHEMCS2S5Packets OBJECT-TYPE
	SYNTAX		Counter64
	MAX-ACCESS read-only
	STATUS		current
	DESCRIPTION
		"Aggregated number of downlink packet received for HE MCS2 5 Spatial Streams
		Device Allocation: AP"
	::= { dlWlanHEMCSPackets 51 }

dlWLanHEMCS3S5Packets OBJECT-TYPE
	SYNTAX		Counter64
	MAX-ACCESS read-only
	STATUS		current
	DESCRIPTION
		"Aggregated number of downlink packet received for HE MCS3 5 Spatial Streams
		Device Allocation: AP"
	::= { dlWlanHEMCSPackets 52 }

dlWLanHEMCS4S5Packets OBJECT-TYPE
	SYNTAX		Counter64
	MAX-ACCESS read-only
	STATUS		current
	DESCRIPTION
		"Aggregated number of downlink packet received for HE MCS4 5 Spatial Streams
		Device Allocation: AP"
	::= { dlWlanHEMCSPackets 53 }

dlWLanHEMCS5S5Packets OBJECT-TYPE
	SYNTAX		Counter64
	MAX-ACCESS read-only
	STATUS		current
	DESCRIPTION
		"Aggregated number of downlink packet received for HE MCS5 5 Spatial Streams
		Device Allocation: AP"
	::= { dlWlanHEMCSPackets 54 }

dlWLanHEMCS6S5Packets OBJECT-TYPE
	SYNTAX		Counter64
	MAX-ACCESS read-only
	STATUS		current
	DESCRIPTION
		"Aggregated number of downlink packet received for HE MCS6 5 Spatial Streams
		Device Allocation: AP"
	::= { dlWlanHEMCSPackets 55 }

dlWLanHEMCS7S5Packets OBJECT-TYPE
	SYNTAX		Counter64
	MAX-ACCESS read-only
	STATUS		current
	DESCRIPTION
		"Aggregated number of downlink packet received for HE MCS7 5 Spatial Streams
		Device Allocation: AP"
	::= { dlWlanHEMCSPackets 56 }

dlWLanHEMCS8S5Packets OBJECT-TYPE
	SYNTAX		Counter64
	MAX-ACCESS read-only
	STATUS		current
	DESCRIPTION
		"Aggregated number of downlink packet received for HE MCS8 5 Spatial Streams
		Device Allocation: AP"
	::= { dlWlanHEMCSPackets 57 }

dlWLanHEMCS9S5Packets OBJECT-TYPE
	SYNTAX		Counter64
	MAX-ACCESS read-only
	STATUS		current
	DESCRIPTION
		"Aggregated number of downlink packet received for HE MCS9 5 Spatial Streams
		Device Allocation: AP"
	::= { dlWlanHEMCSPackets 58 }

dlWLanHEMCS10S5Packets OBJECT-TYPE
	SYNTAX		Counter64
	MAX-ACCESS read-only
	STATUS		current
	DESCRIPTION
		"Aggregated number of downlink packet received for HE MCS10 5 Spatial Streams
		Device Allocation: AP"
	::= { dlWlanHEMCSPackets 59 }

dlWLanHEMCS11S5Packets OBJECT-TYPE
	SYNTAX		Counter64
	MAX-ACCESS read-only
	STATUS		current
	DESCRIPTION
		"Aggregated number of downlink packet received for HE MCS11 5 Spatial Streams
		Device Allocation: AP"
	::= { dlWlanHEMCSPackets 60 }

dlWLanHEMCS0S6Packets OBJECT-TYPE
	SYNTAX		Counter64
	MAX-ACCESS read-only
	STATUS		current
	DESCRIPTION
		"Aggregated number of downlink packet received for HE MCS0 6 Spatial Streams
		Device Allocation: AP"
	::= { dlWlanHEMCSPackets 61 }

dlWLanHEMCS1S6Packets OBJECT-TYPE
	SYNTAX		Counter64
	MAX-ACCESS read-only
	STATUS		current
	DESCRIPTION
		"Aggregated number of downlink packet received for HE MCS1 6 Spatial Streams
		Device Allocation: AP"
	::= { dlWlanHEMCSPackets 62 }

dlWLanHEMCS2S6Packets OBJECT-TYPE
	SYNTAX		Counter64
	MAX-ACCESS read-only
	STATUS		current
	DESCRIPTION
		"Aggregated number of downlink packet received for HE MCS2 6 Spatial Streams
		Device Allocation: AP"
	::= { dlWlanHEMCSPackets 63 }

dlWLanHEMCS3S6Packets OBJECT-TYPE
	SYNTAX		Counter64
	MAX-ACCESS read-only
	STATUS		current
	DESCRIPTION
		"Aggregated number of downlink packet received for HE MCS3 6 Spatial Streams
		Device Allocation: AP"
	::= { dlWlanHEMCSPackets 64 }

dlWLanHEMCS4S6Packets OBJECT-TYPE
	SYNTAX		Counter64
	MAX-ACCESS read-only
	STATUS		current
	DESCRIPTION
		"Aggregated number of downlink packet received for HE MCS4 6 Spatial Streams
		Device Allocation: AP"
	::= { dlWlanHEMCSPackets 65 }

dlWLanHEMCS5S6Packets OBJECT-TYPE
	SYNTAX		Counter64
	MAX-ACCESS read-only
	STATUS		current
	DESCRIPTION
		"Aggregated number of downlink packet received for HE MCS5 6 Spatial Streams
		Device Allocation: AP"
	::= { dlWlanHEMCSPackets 66 }

dlWLanHEMCS6S6Packets OBJECT-TYPE
	SYNTAX		Counter64
	MAX-ACCESS read-only
	STATUS		current
	DESCRIPTION
		"Aggregated number of downlink packet received for HE MCS6 6 Spatial Streams
		Device Allocation: AP"
	::= { dlWlanHEMCSPackets 67 }

dlWLanHEMCS7S6Packets OBJECT-TYPE
	SYNTAX		Counter64
	MAX-ACCESS read-only
	STATUS		current
	DESCRIPTION
		"Aggregated number of downlink packet received for HE MCS7 6 Spatial Streams
		Device Allocation: AP"
	::= { dlWlanHEMCSPackets 68 }

dlWLanHEMCS8S6Packets OBJECT-TYPE
	SYNTAX		Counter64
	MAX-ACCESS read-only
	STATUS		current
	DESCRIPTION
		"Aggregated number of downlink packet received for HE MCS8 6 Spatial Streams
		Device Allocation: AP"
	::= { dlWlanHEMCSPackets 69 }

dlWLanHEMCS9S6Packets OBJECT-TYPE
	SYNTAX		Counter64
	MAX-ACCESS read-only
	STATUS		current
	DESCRIPTION
		"Aggregated number of downlink packet received for HE MCS9 6 Spatial Streams
		Device Allocation: AP"
	::= { dlWlanHEMCSPackets 70 }

dlWLanHEMCS10S6Packets OBJECT-TYPE
	SYNTAX		Counter64
	MAX-ACCESS read-only
	STATUS		current
	DESCRIPTION
		"Aggregated number of downlink packet received for HE MCS10 6 Spatial Streams
		Device Allocation: AP"
	::= { dlWlanHEMCSPackets 71 }

dlWLanHEMCS11S6Packets OBJECT-TYPE
	SYNTAX		Counter64
	MAX-ACCESS read-only
	STATUS		current
	DESCRIPTION
		"Aggregated number of downlink packet received for HE MCS11 6 Spatial Streams
		Device Allocation: AP"
	::= { dlWlanHEMCSPackets 72 }

dlWLanHEMCS0S7Packets OBJECT-TYPE
	SYNTAX		Counter64
	MAX-ACCESS read-only
	STATUS		current
	DESCRIPTION
		"Aggregated number of downlink packet received for HE MCS0 7 Spatial Streams
		Device Allocation: AP"
	::= { dlWlanHEMCSPackets 73 }

dlWLanHEMCS1S7Packets OBJECT-TYPE
	SYNTAX		Counter64
	MAX-ACCESS read-only
	STATUS		current
	DESCRIPTION
		"Aggregated number of downlink packet received for HE MCS1 7 Spatial Streams
		Device Allocation: AP"
	::= { dlWlanHEMCSPackets 74 }

dlWLanHEMCS2S7Packets OBJECT-TYPE
	SYNTAX		Counter64
	MAX-ACCESS read-only
	STATUS		current
	DESCRIPTION
		"Aggregated number of downlink packet received for HE MCS2 7 Spatial Streams
		Device Allocation: AP"
	::= { dlWlanHEMCSPackets 75 }

dlWLanHEMCS3S7Packets OBJECT-TYPE
	SYNTAX		Counter64
	MAX-ACCESS read-only
	STATUS		current
	DESCRIPTION
		"Aggregated number of downlink packet received for HE MCS3 7 Spatial Streams
		Device Allocation: AP"
	::= { dlWlanHEMCSPackets 76 }

dlWLanHEMCS4S7Packets OBJECT-TYPE
	SYNTAX		Counter64
	MAX-ACCESS read-only
	STATUS		current
	DESCRIPTION
		"Aggregated number of downlink packet received for HE MCS4 7 Spatial Streams
		Device Allocation: AP"
	::= { dlWlanHEMCSPackets 77 }

dlWLanHEMCS5S7Packets OBJECT-TYPE
	SYNTAX		Counter64
	MAX-ACCESS read-only
	STATUS		current
	DESCRIPTION
		"Aggregated number of downlink packet received for HE MCS5 7 Spatial Streams
		Device Allocation: AP"
	::= { dlWlanHEMCSPackets 78 }

dlWLanHEMCS6S7Packets OBJECT-TYPE
	SYNTAX		Counter64
	MAX-ACCESS read-only
	STATUS		current
	DESCRIPTION
		"Aggregated number of downlink packet received for HE MCS6 7 Spatial Streams
		Device Allocation: AP"
	::= { dlWlanHEMCSPackets 79 }

dlWLanHEMCS7S7Packets OBJECT-TYPE
	SYNTAX		Counter64
	MAX-ACCESS read-only
	STATUS		current
	DESCRIPTION
		"Aggregated number of downlink packet received for HE MCS7 7 Spatial Streams
		Device Allocation: AP"
	::= { dlWlanHEMCSPackets 80 }

dlWLanHEMCS8S7Packets OBJECT-TYPE
	SYNTAX		Counter64
	MAX-ACCESS read-only
	STATUS		current
	DESCRIPTION
		"Aggregated number of downlink packet received for HE MCS8 7 Spatial Streams
		Device Allocation: AP"
	::= { dlWlanHEMCSPackets 81 }

dlWLanHEMCS9S7Packets OBJECT-TYPE
	SYNTAX		Counter64
	MAX-ACCESS read-only
	STATUS		current
	DESCRIPTION
		"Aggregated number of downlink packet received for HE MCS9 7 Spatial Streams
		Device Allocation: AP"
	::= { dlWlanHEMCSPackets 82 }

dlWLanHEMCS10S7Packets OBJECT-TYPE
	SYNTAX		Counter64
	MAX-ACCESS read-only
	STATUS		current
	DESCRIPTION
		"Aggregated number of downlink packet received for HE MCS10 7 Spatial Streams
		Device Allocation: AP"
	::= { dlWlanHEMCSPackets 83 }

dlWLanHEMCS11S7Packets OBJECT-TYPE
	SYNTAX		Counter64
	MAX-ACCESS read-only
	STATUS		current
	DESCRIPTION
		"Aggregated number of downlink packet received for HE MCS11 7 Spatial Streams
		Device Allocation: AP"
	::= { dlWlanHEMCSPackets 84 }

dlWLanHEMCS0S8Packets OBJECT-TYPE
	SYNTAX		Counter64
	MAX-ACCESS read-only
	STATUS		current
	DESCRIPTION
		"Aggregated number of downlink packet received for HE MCS0 8 Spatial Streams
		Device Allocation: AP"
	::= { dlWlanHEMCSPackets 85 }

dlWLanHEMCS1S8Packets OBJECT-TYPE
	SYNTAX		Counter64
	MAX-ACCESS read-only
	STATUS		current
	DESCRIPTION
		"Aggregated number of downlink packet received for HE MCS1 8 Spatial Streams
		Device Allocation: AP"
	::= { dlWlanHEMCSPackets 86 }

dlWLanHEMCS2S8Packets OBJECT-TYPE
	SYNTAX		Counter64
	MAX-ACCESS read-only
	STATUS		current
	DESCRIPTION
		"Aggregated number of downlink packet received for HE MCS2 8 Spatial Streams
		Device Allocation: AP"
	::= { dlWlanHEMCSPackets 87 }

dlWLanHEMCS3S8Packets OBJECT-TYPE
	SYNTAX		Counter64
	MAX-ACCESS read-only
	STATUS		current
	DESCRIPTION
		"Aggregated number of downlink packet received for HE MCS3 8 Spatial Streams
		Device Allocation: AP"
	::= { dlWlanHEMCSPackets 88 }

dlWLanHEMCS4S8Packets OBJECT-TYPE
	SYNTAX		Counter64
	MAX-ACCESS read-only
	STATUS		current
	DESCRIPTION
		"Aggregated number of downlink packet received for HE MCS4 8 Spatial Streams
		Device Allocation: AP"
	::= { dlWlanHEMCSPackets 89 }

dlWLanHEMCS5S8Packets OBJECT-TYPE
	SYNTAX		Counter64
	MAX-ACCESS read-only
	STATUS		current
	DESCRIPTION
		"Aggregated number of downlink packet received for HE MCS5 8 Spatial Streams
		Device Allocation: AP"
	::= { dlWlanHEMCSPackets 90 }

dlWLanHEMCS6S8Packets OBJECT-TYPE
	SYNTAX		Counter64
	MAX-ACCESS read-only
	STATUS		current
	DESCRIPTION
		"Aggregated number of downlink packet received for HE MCS6 8 Spatial Streams
		Device Allocation: AP"
	::= { dlWlanHEMCSPackets 91 }

dlWLanHEMCS7S8Packets OBJECT-TYPE
	SYNTAX		Counter64
	MAX-ACCESS read-only
	STATUS		current
	DESCRIPTION
		"Aggregated number of downlink packet received for HE MCS7 8 Spatial Streams
		Device Allocation: AP"
	::= { dlWlanHEMCSPackets 92 }

dlWLanHEMCS8S8Packets OBJECT-TYPE
	SYNTAX		Counter64
	MAX-ACCESS read-only
	STATUS		current
	DESCRIPTION
		"Aggregated number of downlink packet received for HE MCS8 8 Spatial Streams
		Device Allocation: AP"
	::= { dlWlanHEMCSPackets 93 }

dlWLanHEMCS9S8Packets OBJECT-TYPE
	SYNTAX		Counter64
	MAX-ACCESS read-only
	STATUS		current
	DESCRIPTION
		"Aggregated number of downlink packet received for HE MCS9 8 Spatial Streams
		Device Allocation: AP"
	::= { dlWlanHEMCSPackets 94 }

dlWLanHEMCS10S8Packets OBJECT-TYPE
	SYNTAX		Counter64
	MAX-ACCESS read-only
	STATUS		current
	DESCRIPTION
		"Aggregated number of downlink packet received for HE MCS10 8 Spatial Streams
		Device Allocation: AP"
	::= { dlWlanHEMCSPackets 95 }

dlWLanHEMCS11S8Packets OBJECT-TYPE
	SYNTAX		Counter64
	MAX-ACCESS read-only
	STATUS		current
	DESCRIPTION
		"Aggregated number of downlink packet received for HE MCS11 8 Spatial Streams
		Device Allocation: AP"
	::= { dlWlanHEMCSPackets 96 }

dlWLanHEMCS12S1Packets OBJECT-TYPE
	SYNTAX		Counter64
	MAX-ACCESS read-only
	STATUS		current
	DESCRIPTION
		"Aggregated number of downlink packet received for HE MCS12 1 Spatial Streams
		Device Allocation: AP"
	::= { dlWlanHEMCSPackets 97 }

dlWLanHEMCS13S1Packets OBJECT-TYPE
	SYNTAX		Counter64
	MAX-ACCESS read-only
	STATUS		current
	DESCRIPTION
		"Aggregated number of downlink packet received for HE MCS13 1 Spatial Streams
		Device Allocation: AP"
	::= { dlWlanHEMCSPackets 98 }

dlWLanHEMCS12S2Packets OBJECT-TYPE
	SYNTAX		Counter64
	MAX-ACCESS read-only
	STATUS		current
	DESCRIPTION
		"Aggregated number of downlink packet received for HE MCS12 2 Spatial Streams
		Device Allocation: AP"
	::= { dlWlanHEMCSPackets 99 }

dlWLanHEMCS13S2Packets OBJECT-TYPE
	SYNTAX		Counter64
	MAX-ACCESS read-only
	STATUS		current
	DESCRIPTION
		"Aggregated number of downlink packet received for HE MCS13 2 Spatial Streams
		Device Allocation: AP"
	::= { dlWlanHEMCSPackets 100 }

dlWLanHEMCS12S3Packets OBJECT-TYPE
	SYNTAX		Counter64
	MAX-ACCESS read-only
	STATUS		current
	DESCRIPTION
		"Aggregated number of downlink packet received for HE MCS12 3 Spatial Streams
		Device Allocation: AP"
	::= { dlWlanHEMCSPackets 101 }

dlWLanHEMCS13S3Packets OBJECT-TYPE
	SYNTAX		Counter64
	MAX-ACCESS read-only
	STATUS		current
	DESCRIPTION
		"Aggregated number of downlink packet received for HE MCS13 3 Spatial Streams
		Device Allocation: AP"
	::= { dlWlanHEMCSPackets 102 }

dlWLanHEMCS12S4Packets OBJECT-TYPE
	SYNTAX		Counter64
	MAX-ACCESS read-only
	STATUS		current
	DESCRIPTION
		"Aggregated number of downlink packet received for HE MCS12 4 Spatial Streams
		Device Allocation: AP"
	::= { dlWlanHEMCSPackets 103 }

dlWLanHEMCS13S4Packets OBJECT-TYPE
	SYNTAX		Counter64
	MAX-ACCESS read-only
	STATUS		current
	DESCRIPTION
		"Aggregated number of downlink packet received for HE MCS13 4 Spatial Streams
		Device Allocation: AP"
	::= { dlWlanHEMCSPackets 104 }

dlWLanHEMCS12S5Packets OBJECT-TYPE
	SYNTAX		Counter64
	MAX-ACCESS read-only
	STATUS		current
	DESCRIPTION
		"Aggregated number of downlink packet received for HE MCS12 5 Spatial Streams
		Device Allocation: AP"
	::= { dlWlanHEMCSPackets 105 }

dlWLanHEMCS13S5Packets OBJECT-TYPE
	SYNTAX		Counter64
	MAX-ACCESS read-only
	STATUS		current
	DESCRIPTION
		"Aggregated number of downlink packet received for HE MCS13 5 Spatial Streams
		Device Allocation: AP"
	::= { dlWlanHEMCSPackets 106 }

dlWLanHEMCS12S6Packets OBJECT-TYPE
	SYNTAX		Counter64
	MAX-ACCESS read-only
	STATUS		current
	DESCRIPTION
		"Aggregated number of downlink packet received for HE MCS12 6 Spatial Streams
		Device Allocation: AP"
	::= { dlWlanHEMCSPackets 107 }

dlWLanHEMCS13S6Packets OBJECT-TYPE
	SYNTAX		Counter64
	MAX-ACCESS read-only
	STATUS		current
	DESCRIPTION
		"Aggregated number of downlink packet received for HE MCS13 6 Spatial Streams
		Device Allocation: AP"
	::= { dlWlanHEMCSPackets 108 }

dlWLanHEMCS12S7Packets OBJECT-TYPE
	SYNTAX		Counter64
	MAX-ACCESS read-only
	STATUS		current
	DESCRIPTION
		"Aggregated number of downlink packet received for HE MCS12 7 Spatial Streams
		Device Allocation: AP"
	::= { dlWlanHEMCSPackets 109 }

dlWLanHEMCS13S7Packets OBJECT-TYPE
	SYNTAX		Counter64
	MAX-ACCESS read-only
	STATUS		current
	DESCRIPTION
		"Aggregated number of downlink packet received for HE MCS13 7 Spatial Streams
		Device Allocation: AP"
	::= { dlWlanHEMCSPackets 110 }

dlWLanHEMCS12S8Packets OBJECT-TYPE
	SYNTAX		Counter64
	MAX-ACCESS read-only
	STATUS		current
	DESCRIPTION
		"Aggregated number of downlink packet received for HE MCS12 8 Spatial Streams
		Device Allocation: AP"
	::= { dlWlanHEMCSPackets 111 }

dlWLanHEMCS13S8Packets OBJECT-TYPE
	SYNTAX		Counter64
	MAX-ACCESS read-only
	STATUS		current
	DESCRIPTION
		"Aggregated number of downlink packet received for HE MCS13 8 Spatial Streams
		Device Allocation: AP"
	::= { dlWlanHEMCSPackets 112 }

ulWLanHEMCS0S1Packets OBJECT-TYPE
	SYNTAX		Counter64
	MAX-ACCESS read-only
	STATUS		current
	DESCRIPTION
		"Aggregated number of uplink packet received for HE MCS0 1 Spatial Stream
		Device Allocation: AP"
	::= { ulWlanHEMCSPackets 1 }

ulWLanHEMCS1S1Packets OBJECT-TYPE
	SYNTAX		Counter64
	MAX-ACCESS read-only
	STATUS		current
	DESCRIPTION
		"Aggregated number of uplink packet received for HE MCS1 1 Spatial Stream
		Device Allocation: AP"
	::= { ulWlanHEMCSPackets 2 }

ulWLanHEMCS2S1Packets OBJECT-TYPE
	SYNTAX		Counter64
	MAX-ACCESS read-only
	STATUS		current
	DESCRIPTION
		"Aggregated number of uplink packet received for HE MCS2 1 Spatial Stream
		Device Allocation: AP"
	::= { ulWlanHEMCSPackets 3 }

ulWLanHEMCS3S1Packets OBJECT-TYPE
	SYNTAX		Counter64
	MAX-ACCESS read-only
	STATUS		current
	DESCRIPTION
		"Aggregated number of uplink packet received for HE MCS3 1 Spatial Stream
		Device Allocation: AP"
	::= { ulWlanHEMCSPackets 4 }

ulWLanHEMCS4S1Packets OBJECT-TYPE
	SYNTAX		Counter64
	MAX-ACCESS read-only
	STATUS		current
	DESCRIPTION
		"Aggregated number of uplink packet received for HE MCS4 1 Spatial Stream
		Device Allocation: AP"
	::= { ulWlanHEMCSPackets 5 }

ulWLanHEMCS5S1Packets OBJECT-TYPE
	SYNTAX		Counter64
	MAX-ACCESS read-only
	STATUS		current
	DESCRIPTION
		"Aggregated number of uplink packet received for HE MCS5 1 Spatial Stream
		Device Allocation: AP"
	::= { ulWlanHEMCSPackets 6 }

ulWLanHEMCS6S1Packets OBJECT-TYPE
	SYNTAX		Counter64
	MAX-ACCESS read-only
	STATUS		current
	DESCRIPTION
		"Aggregated number of uplink packet received for HE MCS6 1 Spatial Stream
		Device Allocation: AP"
	::= { ulWlanHEMCSPackets 7 }

ulWLanHEMCS7S1Packets OBJECT-TYPE
	SYNTAX		Counter64
	MAX-ACCESS read-only
	STATUS		current
	DESCRIPTION
		"Aggregated number of uplink packet received for HE MCS7 1 Spatial Stream
		Device Allocation: AP"
	::= { ulWlanHEMCSPackets 8 }

ulWLanHEMCS8S1Packets OBJECT-TYPE
	SYNTAX		Counter64
	MAX-ACCESS read-only
	STATUS		current
	DESCRIPTION
		"Aggregated number of uplink packet received for HE MCS8 1 Spatial Stream
		Device Allocation: AP"
	::= { ulWlanHEMCSPackets 9 }

ulWLanHEMCS9S1Packets OBJECT-TYPE
	SYNTAX		Counter64
	MAX-ACCESS read-only
	STATUS		current
	DESCRIPTION
		"Aggregated number of uplink packet received for HE MCS9 1 Spatial Stream
		Device Allocation: AP"
	::= { ulWlanHEMCSPackets 10 }

ulWLanHEMCS10S1Packets OBJECT-TYPE
	SYNTAX		Counter64
	MAX-ACCESS read-only
	STATUS		current
	DESCRIPTION
		"Aggregated number of uplink packet received for HE MCS10 1 Spatial Stream
		Device Allocation: AP"
	::= { ulWlanHEMCSPackets 11 }

ulWLanHEMCS11S1Packets OBJECT-TYPE
	SYNTAX		Counter64
	MAX-ACCESS read-only
	STATUS		current
	DESCRIPTION
		"Aggregated number of uplink packet received for HE MCS11 1 Spatial Stream
		Device Allocation: AP"
	::= { ulWlanHEMCSPackets 12 }

ulWLanHEMCS0S2Packets OBJECT-TYPE
	SYNTAX		Counter64
	MAX-ACCESS read-only
	STATUS		current
	DESCRIPTION
		"Aggregated number of uplink packet received for HE MCS0 2 Spatial Streams
		Device Allocation: AP"
	::= { ulWlanHEMCSPackets 13 }

ulWLanHEMCS1S2Packets OBJECT-TYPE
	SYNTAX		Counter64
	MAX-ACCESS read-only
	STATUS		current
	DESCRIPTION
		"Aggregated number of uplink packet received for HE MCS1 2 Spatial Streams
		Device Allocation: AP"
	::= { ulWlanHEMCSPackets 14 }

ulWLanHEMCS2S2Packets OBJECT-TYPE
	SYNTAX		Counter64
	MAX-ACCESS read-only
	STATUS		current
	DESCRIPTION
		"Aggregated number of uplink packet received for HE MCS2 2 Spatial Streams
		Device Allocation: AP"
	::= { ulWlanHEMCSPackets 15 }

ulWLanHEMCS3S2Packets OBJECT-TYPE
	SYNTAX		Counter64
	MAX-ACCESS read-only
	STATUS		current
	DESCRIPTION
		"Aggregated number of uplink packet received for HE MCS3 2 Spatial Streams
		Device Allocation: AP"
	::= { ulWlanHEMCSPackets 16 }

ulWLanHEMCS4S2Packets OBJECT-TYPE
	SYNTAX		Counter64
	MAX-ACCESS read-only
	STATUS		current
	DESCRIPTION
		"Aggregated number of uplink packet received for HE MCS4 2 Spatial Streams
		Device Allocation: AP"
	::= { ulWlanHEMCSPackets 17 }

ulWLanHEMCS5S2Packets OBJECT-TYPE
	SYNTAX		Counter64
	MAX-ACCESS read-only
	STATUS		current
	DESCRIPTION
		"Aggregated number of uplink packet received for HE MCS5 2 Spatial Streams
		Device Allocation: AP"
	::= { ulWlanHEMCSPackets 18 }

ulWLanHEMCS6S2Packets OBJECT-TYPE
	SYNTAX		Counter64
	MAX-ACCESS read-only
	STATUS		current
	DESCRIPTION
		"Aggregated number of uplink packet received for HE MCS6 2 Spatial Streams
		Device Allocation: AP"
	::= { ulWlanHEMCSPackets 19 }

ulWLanHEMCS7S2Packets OBJECT-TYPE
	SYNTAX		Counter64
	MAX-ACCESS read-only
	STATUS		current
	DESCRIPTION
		"Aggregated number of uplink packet received for HE MCS7 2 Spatial Streams
		Device Allocation: AP"
	::= { ulWlanHEMCSPackets 20 }

ulWLanHEMCS8S2Packets OBJECT-TYPE
	SYNTAX		Counter64
	MAX-ACCESS read-only
	STATUS		current
	DESCRIPTION
		"Aggregated number of uplink packet received for HE MCS8 2 Spatial Streams
		Device Allocation: AP"
	::= { ulWlanHEMCSPackets 21 }

ulWLanHEMCS9S2Packets OBJECT-TYPE
	SYNTAX		Counter64
	MAX-ACCESS read-only
	STATUS		current
	DESCRIPTION
		"Aggregated number of uplink packet received for HE MCS9 2 Spatial Streams
		Device Allocation: AP"
	::= { ulWlanHEMCSPackets 22 }

ulWLanHEMCS10S2Packets OBJECT-TYPE
	SYNTAX		Counter64
	MAX-ACCESS read-only
	STATUS		current
	DESCRIPTION
		"Aggregated number of uplink packet received for HE MCS10 2 Spatial Streams
		Device Allocation: AP"
	::= { ulWlanHEMCSPackets 23 }

ulWLanHEMCS11S2Packets OBJECT-TYPE
	SYNTAX		Counter64
	MAX-ACCESS read-only
	STATUS		current
	DESCRIPTION
		"Aggregated number of uplink packet received for HE MCS11 2 Spatial Streams
		Device Allocation: AP"
	::= { ulWlanHEMCSPackets 24 }

ulWLanHEMCS0S3Packets OBJECT-TYPE
	SYNTAX		Counter64
	MAX-ACCESS read-only
	STATUS		current
	DESCRIPTION
		"Aggregated number of uplink packet received for HE MCS0 3 Spatial Streams
		Device Allocation: AP"
	::= { ulWlanHEMCSPackets 25 }

ulWLanHEMCS1S3Packets OBJECT-TYPE
	SYNTAX		Counter64
	MAX-ACCESS read-only
	STATUS		current
	DESCRIPTION
		"Aggregated number of uplink packet received for HE MCS1 3 Spatial Streams
		Device Allocation: AP"
	::= { ulWlanHEMCSPackets 26 }

ulWLanHEMCS2S3Packets OBJECT-TYPE
	SYNTAX		Counter64
	MAX-ACCESS read-only
	STATUS		current
	DESCRIPTION
		"Aggregated number of uplink packet received for HE MCS2 3 Spatial Streams
		Device Allocation: AP"
	::= { ulWlanHEMCSPackets 27 }

ulWLanHEMCS3S3Packets OBJECT-TYPE
	SYNTAX		Counter64
	MAX-ACCESS read-only
	STATUS		current
	DESCRIPTION
		"Aggregated number of uplink packet received for HE MCS3 3 Spatial Streams
		Device Allocation: AP"
	::= { ulWlanHEMCSPackets 28 }

ulWLanHEMCS4S3Packets OBJECT-TYPE
	SYNTAX		Counter64
	MAX-ACCESS read-only
	STATUS		current
	DESCRIPTION
		"Aggregated number of uplink packet received for HE MCS4 3 Spatial Streams
		Device Allocation: AP"
	::= { ulWlanHEMCSPackets 29 }

ulWLanHEMCS5S3Packets OBJECT-TYPE
	SYNTAX		Counter64
	MAX-ACCESS read-only
	STATUS		current
	DESCRIPTION
		"Aggregated number of uplink packet received for HE MCS5 3 Spatial Streams
		Device Allocation: AP"
	::= { ulWlanHEMCSPackets 30 }

ulWLanHEMCS6S3Packets OBJECT-TYPE
	SYNTAX		Counter64
	MAX-ACCESS read-only
	STATUS		current
	DESCRIPTION
		"Aggregated number of uplink packet received for HE MCS6 3 Spatial Streams
		Device Allocation: AP"
	::= { ulWlanHEMCSPackets 31 }

ulWLanHEMCS7S3Packets OBJECT-TYPE
	SYNTAX		Counter64
	MAX-ACCESS read-only
	STATUS		current
	DESCRIPTION
		"Aggregated number of uplink packet received for HE MCS7 3 Spatial Streams
		Device Allocation: AP"
	::= { ulWlanHEMCSPackets 32 }

ulWLanHEMCS8S3Packets OBJECT-TYPE
	SYNTAX		Counter64
	MAX-ACCESS read-only
	STATUS		current
	DESCRIPTION
		"Aggregated number of uplink packet received for HE MCS8 3 Spatial Streams
		Device Allocation: AP"
	::= { ulWlanHEMCSPackets 33 }

ulWLanHEMCS9S3Packets OBJECT-TYPE
	SYNTAX		Counter64
	MAX-ACCESS read-only
	STATUS		current
	DESCRIPTION
		"Aggregated number of uplink packet received for HE MCS9 3 Spatial Streams
		Device Allocation: AP"
	::= { ulWlanHEMCSPackets 34 }

ulWLanHEMCS10S3Packets OBJECT-TYPE
	SYNTAX		Counter64
	MAX-ACCESS read-only
	STATUS		current
	DESCRIPTION
		"Aggregated number of uplink packet received for HE MCS10 3 Spatial Streams
		Device Allocation: AP"
	::= { ulWlanHEMCSPackets 35 }

ulWLanHEMCS11S3Packets OBJECT-TYPE
	SYNTAX		Counter64
	MAX-ACCESS read-only
	STATUS		current
	DESCRIPTION
		"Aggregated number of uplink packet received for HE MCS11 3 Spatial Streams
		Device Allocation: AP"
	::= { ulWlanHEMCSPackets 36 }

ulWLanHEMCS0S4Packets OBJECT-TYPE
	SYNTAX		Counter64
	MAX-ACCESS read-only
	STATUS		current
	DESCRIPTION
		"Aggregated number of uplink packet received for HE MCS0 4 Spatial Streams
		Device Allocation: AP"
	::= { ulWlanHEMCSPackets 37 }

ulWLanHEMCS1S4Packets OBJECT-TYPE
	SYNTAX		Counter64
	MAX-ACCESS read-only
	STATUS		current
	DESCRIPTION
		"Aggregated number of uplink packet received for HE MCS1 4 Spatial Streams
		Device Allocation: AP"
	::= { ulWlanHEMCSPackets 38 }

ulWLanHEMCS2S4Packets OBJECT-TYPE
	SYNTAX		Counter64
	MAX-ACCESS read-only
	STATUS		current
	DESCRIPTION
		"Aggregated number of uplink packet received for HE MCS2 4 Spatial Streams
		Device Allocation: AP"
	::= { ulWlanHEMCSPackets 39 }

ulWLanHEMCS3S4Packets OBJECT-TYPE
	SYNTAX		Counter64
	MAX-ACCESS read-only
	STATUS		current
	DESCRIPTION
		"Aggregated number of uplink packet received for HE MCS3 4 Spatial Streams
		Device Allocation: AP"
	::= { ulWlanHEMCSPackets 40 }

ulWLanHEMCS4S4Packets OBJECT-TYPE
	SYNTAX		Counter64
	MAX-ACCESS read-only
	STATUS		current
	DESCRIPTION
		"Aggregated number of uplink packet received for HE MCS4 4 Spatial Streams
		Device Allocation: AP"
	::= { ulWlanHEMCSPackets 41 }

ulWLanHEMCS5S4Packets OBJECT-TYPE
	SYNTAX		Counter64
	MAX-ACCESS read-only
	STATUS		current
	DESCRIPTION
		"Aggregated number of uplink packet received for HE MCS5 4 Spatial Streams
		Device Allocation: AP"
	::= { ulWlanHEMCSPackets 42 }

ulWLanHEMCS6S4Packets OBJECT-TYPE
	SYNTAX		Counter64
	MAX-ACCESS read-only
	STATUS		current
	DESCRIPTION
		"Aggregated number of uplink packet received for HE MCS6 4 Spatial Streams
		Device Allocation: AP"
	::= { ulWlanHEMCSPackets 43 }

ulWLanHEMCS7S4Packets OBJECT-TYPE
	SYNTAX		Counter64
	MAX-ACCESS read-only
	STATUS		current
	DESCRIPTION
		"Aggregated number of uplink packet received for HE MCS7 4 Spatial Streams
		Device Allocation: AP"
	::= { ulWlanHEMCSPackets 44 }

ulWLanHEMCS8S4Packets OBJECT-TYPE
	SYNTAX		Counter64
	MAX-ACCESS read-only
	STATUS		current
	DESCRIPTION
		"Aggregated number of uplink packet received for HE MCS8 4 Spatial Streams
		Device Allocation: AP"
	::= { ulWlanHEMCSPackets 45 }

ulWLanHEMCS9S4Packets OBJECT-TYPE
	SYNTAX		Counter64
	MAX-ACCESS read-only
	STATUS		current
	DESCRIPTION
		"Aggregated number of uplink packet received for HE MCS9 4 Spatial Streams
		Device Allocation: AP"
	::= { ulWlanHEMCSPackets 46 }

ulWLanHEMCS10S4Packets OBJECT-TYPE
	SYNTAX		Counter64
	MAX-ACCESS read-only
	STATUS		current
	DESCRIPTION
		"Aggregated number of uplink packet received for HE MCS10 4 Spatial Streams
		Device Allocation: AP"
	::= { ulWlanHEMCSPackets 47 }

ulWLanHEMCS11S4Packets OBJECT-TYPE
	SYNTAX		Counter64
	MAX-ACCESS read-only
	STATUS		current
	DESCRIPTION
		"Aggregated number of uplink packet received for HE MCS11 4 Spatial Streams
		Device Allocation: AP"
	::= { ulWlanHEMCSPackets 48 }

ulWLanHEMCS0S5Packets OBJECT-TYPE
	SYNTAX		Counter64
	MAX-ACCESS read-only
	STATUS		current
	DESCRIPTION
		"Aggregated number of uplink packet received for HE MCS0 5 Spatial Streams
		Device Allocation: AP"
	::= { ulWlanHEMCSPackets 49 }

ulWLanHEMCS1S5Packets OBJECT-TYPE
	SYNTAX		Counter64
	MAX-ACCESS read-only
	STATUS		current
	DESCRIPTION
		"Aggregated number of uplink packet received for HE MCS1 5 Spatial Streams
		Device Allocation: AP"
	::= { ulWlanHEMCSPackets 50 }

ulWLanHEMCS2S5Packets OBJECT-TYPE
	SYNTAX		Counter64
	MAX-ACCESS read-only
	STATUS		current
	DESCRIPTION
		"Aggregated number of uplink packet received for HE MCS2 5 Spatial Streams
		Device Allocation: AP"
	::= { ulWlanHEMCSPackets 51 }

ulWLanHEMCS3S5Packets OBJECT-TYPE
	SYNTAX		Counter64
	MAX-ACCESS read-only
	STATUS		current
	DESCRIPTION
		"Aggregated number of uplink packet received for HE MCS3 5 Spatial Streams
		Device Allocation: AP"
	::= { ulWlanHEMCSPackets 52 }

ulWLanHEMCS4S5Packets OBJECT-TYPE
	SYNTAX		Counter64
	MAX-ACCESS read-only
	STATUS		current
	DESCRIPTION
		"Aggregated number of uplink packet received for HE MCS4 5 Spatial Streams
		Device Allocation: AP"
	::= { ulWlanHEMCSPackets 53 }

ulWLanHEMCS5S5Packets OBJECT-TYPE
	SYNTAX		Counter64
	MAX-ACCESS read-only
	STATUS		current
	DESCRIPTION
		"Aggregated number of uplink packet received for HE MCS5 5 Spatial Streams
		Device Allocation: AP"
	::= { ulWlanHEMCSPackets 54 }

ulWLanHEMCS6S5Packets OBJECT-TYPE
	SYNTAX		Counter64
	MAX-ACCESS read-only
	STATUS		current
	DESCRIPTION
		"Aggregated number of uplink packet received for HE MCS6 5 Spatial Streams
		Device Allocation: AP"
	::= { ulWlanHEMCSPackets 55 }

ulWLanHEMCS7S5Packets OBJECT-TYPE
	SYNTAX		Counter64
	MAX-ACCESS read-only
	STATUS		current
	DESCRIPTION
		"Aggregated number of uplink packet received for HE MCS7 5 Spatial Streams
		Device Allocation: AP"
	::= { ulWlanHEMCSPackets 56 }

ulWLanHEMCS8S5Packets OBJECT-TYPE
	SYNTAX		Counter64
	MAX-ACCESS read-only
	STATUS		current
	DESCRIPTION
		"Aggregated number of uplink packet received for HE MCS8 5 Spatial Streams
		Device Allocation: AP"
	::= { ulWlanHEMCSPackets 57 }

ulWLanHEMCS9S5Packets OBJECT-TYPE
	SYNTAX		Counter64
	MAX-ACCESS read-only
	STATUS		current
	DESCRIPTION
		"Aggregated number of uplink packet received for HE MCS9 5 Spatial Streams
		Device Allocation: AP"
	::= { ulWlanHEMCSPackets 58 }

ulWLanHEMCS10S5Packets OBJECT-TYPE
	SYNTAX		Counter64
	MAX-ACCESS read-only
	STATUS		current
	DESCRIPTION
		"Aggregated number of uplink packet received for HE MCS10 5 Spatial Streams
		Device Allocation: AP"
	::= { ulWlanHEMCSPackets 59 }

ulWLanHEMCS11S5Packets OBJECT-TYPE
	SYNTAX		Counter64
	MAX-ACCESS read-only
	STATUS		current
	DESCRIPTION
		"Aggregated number of uplink packet received for HE MCS11 5 Spatial Streams
		Device Allocation: AP"
	::= { ulWlanHEMCSPackets 60 }

ulWLanHEMCS0S6Packets OBJECT-TYPE
	SYNTAX		Counter64
	MAX-ACCESS read-only
	STATUS		current
	DESCRIPTION
		"Aggregated number of uplink packet received for HE MCS0 6 Spatial Streams
		Device Allocation: AP"
	::= { ulWlanHEMCSPackets 61 }

ulWLanHEMCS1S6Packets OBJECT-TYPE
	SYNTAX		Counter64
	MAX-ACCESS read-only
	STATUS		current
	DESCRIPTION
		"Aggregated number of uplink packet received for HE MCS1 6 Spatial Streams
		Device Allocation: AP"
	::= { ulWlanHEMCSPackets 62 }

ulWLanHEMCS2S6Packets OBJECT-TYPE
	SYNTAX		Counter64
	MAX-ACCESS read-only
	STATUS		current
	DESCRIPTION
		"Aggregated number of uplink packet received for HE MCS2 6 Spatial Streams
		Device Allocation: AP"
	::= { ulWlanHEMCSPackets 63 }

ulWLanHEMCS3S6Packets OBJECT-TYPE
	SYNTAX		Counter64
	MAX-ACCESS read-only
	STATUS		current
	DESCRIPTION
		"Aggregated number of uplink packet received for HE MCS3 6 Spatial Streams
		Device Allocation: AP"
	::= { ulWlanHEMCSPackets 64 }

ulWLanHEMCS4S6Packets OBJECT-TYPE
	SYNTAX		Counter64
	MAX-ACCESS read-only
	STATUS		current
	DESCRIPTION
		"Aggregated number of uplink packet received for HE MCS4 6 Spatial Streams
		Device Allocation: AP"
	::= { ulWlanHEMCSPackets 65 }

ulWLanHEMCS5S6Packets OBJECT-TYPE
	SYNTAX		Counter64
	MAX-ACCESS read-only
	STATUS		current
	DESCRIPTION
		"Aggregated number of uplink packet received for HE MCS5 6 Spatial Streams
		Device Allocation: AP"
	::= { ulWlanHEMCSPackets 66 }

ulWLanHEMCS6S6Packets OBJECT-TYPE
	SYNTAX		Counter64
	MAX-ACCESS read-only
	STATUS		current
	DESCRIPTION
		"Aggregated number of uplink packet received for HE MCS6 6 Spatial Streams
		Device Allocation: AP"
	::= { ulWlanHEMCSPackets 67 }

ulWLanHEMCS7S6Packets OBJECT-TYPE
	SYNTAX		Counter64
	MAX-ACCESS read-only
	STATUS		current
	DESCRIPTION
		"Aggregated number of uplink packet received for HE MCS7 6 Spatial Streams
		Device Allocation: AP"
	::= { ulWlanHEMCSPackets 68 }

ulWLanHEMCS8S6Packets OBJECT-TYPE
	SYNTAX		Counter64
	MAX-ACCESS read-only
	STATUS		current
	DESCRIPTION
		"Aggregated number of uplink packet received for HE MCS8 6 Spatial Streams
		Device Allocation: AP"
	::= { ulWlanHEMCSPackets 69 }

ulWLanHEMCS9S6Packets OBJECT-TYPE
	SYNTAX		Counter64
	MAX-ACCESS read-only
	STATUS		current
	DESCRIPTION
		"Aggregated number of uplink packet received for HE MCS9 6 Spatial Streams
		Device Allocation: AP"
	::= { ulWlanHEMCSPackets 70 }

ulWLanHEMCS10S6Packets OBJECT-TYPE
	SYNTAX		Counter64
	MAX-ACCESS read-only
	STATUS		current
	DESCRIPTION
		"Aggregated number of uplink packet received for HE MCS10 6 Spatial Streams
		Device Allocation: AP"
	::= { ulWlanHEMCSPackets 71 }

ulWLanHEMCS11S6Packets OBJECT-TYPE
	SYNTAX		Counter64
	MAX-ACCESS read-only
	STATUS		current
	DESCRIPTION
		"Aggregated number of uplink packet received for HE MCS11 6 Spatial Streams
		Device Allocation: AP"
	::= { ulWlanHEMCSPackets 72 }

ulWLanHEMCS0S7Packets OBJECT-TYPE
	SYNTAX		Counter64
	MAX-ACCESS read-only
	STATUS		current
	DESCRIPTION
		"Aggregated number of uplink packet received for HE MCS0 7 Spatial Streams
		Device Allocation: AP"
	::= { ulWlanHEMCSPackets 73 }

ulWLanHEMCS1S7Packets OBJECT-TYPE
	SYNTAX		Counter64
	MAX-ACCESS read-only
	STATUS		current
	DESCRIPTION
		"Aggregated number of uplink packet received for HE MCS1 7 Spatial Streams
		Device Allocation: AP"
	::= { ulWlanHEMCSPackets 74 }

ulWLanHEMCS2S7Packets OBJECT-TYPE
	SYNTAX		Counter64
	MAX-ACCESS read-only
	STATUS		current
	DESCRIPTION
		"Aggregated number of uplink packet received for HE MCS2 7 Spatial Streams
		Device Allocation: AP"
	::= { ulWlanHEMCSPackets 75 }

ulWLanHEMCS3S7Packets OBJECT-TYPE
	SYNTAX		Counter64
	MAX-ACCESS read-only
	STATUS		current
	DESCRIPTION
		"Aggregated number of uplink packet received for HE MCS3 7 Spatial Streams
		Device Allocation: AP"
	::= { ulWlanHEMCSPackets 76 }

ulWLanHEMCS4S7Packets OBJECT-TYPE
	SYNTAX		Counter64
	MAX-ACCESS read-only
	STATUS		current
	DESCRIPTION
		"Aggregated number of uplink packet received for HE MCS4 7 Spatial Streams
		Device Allocation: AP"
	::= { ulWlanHEMCSPackets 77 }

ulWLanHEMCS5S7Packets OBJECT-TYPE
	SYNTAX		Counter64
	MAX-ACCESS read-only
	STATUS		current
	DESCRIPTION
		"Aggregated number of uplink packet received for HE MCS5 7 Spatial Streams
		Device Allocation: AP"
	::= { ulWlanHEMCSPackets 78 }

ulWLanHEMCS6S7Packets OBJECT-TYPE
	SYNTAX		Counter64
	MAX-ACCESS read-only
	STATUS		current
	DESCRIPTION
		"Aggregated number of uplink packet received for HE MCS6 7 Spatial Streams
		Device Allocation: AP"
	::= { ulWlanHEMCSPackets 79 }

ulWLanHEMCS7S7Packets OBJECT-TYPE
	SYNTAX		Counter64
	MAX-ACCESS read-only
	STATUS		current
	DESCRIPTION
		"Aggregated number of uplink packet received for HE MCS7 7 Spatial Streams
		Device Allocation: AP"
	::= { ulWlanHEMCSPackets 80 }

ulWLanHEMCS8S7Packets OBJECT-TYPE
	SYNTAX		Counter64
	MAX-ACCESS read-only
	STATUS		current
	DESCRIPTION
		"Aggregated number of uplink packet received for HE MCS8 7 Spatial Streams
		Device Allocation: AP"
	::= { ulWlanHEMCSPackets 81 }

ulWLanHEMCS9S7Packets OBJECT-TYPE
	SYNTAX		Counter64
	MAX-ACCESS read-only
	STATUS		current
	DESCRIPTION
		"Aggregated number of uplink packet received for HE MCS9 7 Spatial Streams
		Device Allocation: AP"
	::= { ulWlanHEMCSPackets 82 }

ulWLanHEMCS10S7Packets OBJECT-TYPE
	SYNTAX		Counter64
	MAX-ACCESS read-only
	STATUS		current
	DESCRIPTION
		"Aggregated number of uplink packet received for HE MCS10 7 Spatial Streams
		Device Allocation: AP"
	::= { ulWlanHEMCSPackets 83 }

ulWLanHEMCS11S7Packets OBJECT-TYPE
	SYNTAX		Counter64
	MAX-ACCESS read-only
	STATUS		current
	DESCRIPTION
		"Aggregated number of uplink packet received for HE MCS11 7 Spatial Streams
		Device Allocation: AP"
	::= { ulWlanHEMCSPackets 84 }

ulWLanHEMCS0S8Packets OBJECT-TYPE
	SYNTAX		Counter64
	MAX-ACCESS read-only
	STATUS		current
	DESCRIPTION
		"Aggregated number of uplink packet received for HE MCS0 8 Spatial Streams
		Device Allocation: AP"
	::= { ulWlanHEMCSPackets 85 }

ulWLanHEMCS1S8Packets OBJECT-TYPE
	SYNTAX		Counter64
	MAX-ACCESS read-only
	STATUS		current
	DESCRIPTION
		"Aggregated number of uplink packet received for HE MCS1 8 Spatial Streams
		Device Allocation: AP"
	::= { ulWlanHEMCSPackets 86 }

ulWLanHEMCS2S8Packets OBJECT-TYPE
	SYNTAX		Counter64
	MAX-ACCESS read-only
	STATUS		current
	DESCRIPTION
		"Aggregated number of uplink packet received for HE MCS2 8 Spatial Streams
		Device Allocation: AP"
	::= { ulWlanHEMCSPackets 87 }

ulWLanHEMCS3S8Packets OBJECT-TYPE
	SYNTAX		Counter64
	MAX-ACCESS read-only
	STATUS		current
	DESCRIPTION
		"Aggregated number of uplink packet received for HE MCS3 8 Spatial Streams
		Device Allocation: AP"
	::= { ulWlanHEMCSPackets 88 }

ulWLanHEMCS4S8Packets OBJECT-TYPE
	SYNTAX		Counter64
	MAX-ACCESS read-only
	STATUS		current
	DESCRIPTION
		"Aggregated number of uplink packet received for HE MCS4 8 Spatial Streams
		Device Allocation: AP"
	::= { ulWlanHEMCSPackets 89 }

ulWLanHEMCS5S8Packets OBJECT-TYPE
	SYNTAX		Counter64
	MAX-ACCESS read-only
	STATUS		current
	DESCRIPTION
		"Aggregated number of uplink packet received for HE MCS5 8 Spatial Streams
		Device Allocation: AP"
	::= { ulWlanHEMCSPackets 90 }

ulWLanHEMCS6S8Packets OBJECT-TYPE
	SYNTAX		Counter64
	MAX-ACCESS read-only
	STATUS		current
	DESCRIPTION
		"Aggregated number of uplink packet received for HE MCS6 8 Spatial Streams
		Device Allocation: AP"
	::= { ulWlanHEMCSPackets 91 }

ulWLanHEMCS7S8Packets OBJECT-TYPE
	SYNTAX		Counter64
	MAX-ACCESS read-only
	STATUS		current
	DESCRIPTION
		"Aggregated number of uplink packet received for HE MCS7 8 Spatial Streams
		Device Allocation: AP"
	::= { ulWlanHEMCSPackets 92 }

ulWLanHEMCS8S8Packets OBJECT-TYPE
	SYNTAX		Counter64
	MAX-ACCESS read-only
	STATUS		current
	DESCRIPTION
		"Aggregated number of uplink packet received for HE MCS8 8 Spatial Streams
		Device Allocation: AP"
	::= { ulWlanHEMCSPackets 93 }

ulWLanHEMCS9S8Packets OBJECT-TYPE
	SYNTAX		Counter64
	MAX-ACCESS read-only
	STATUS		current
	DESCRIPTION
		"Aggregated number of uplink packet received for HE MCS9 8 Spatial Streams
		Device Allocation: AP"
	::= { ulWlanHEMCSPackets 94 }

ulWLanHEMCS10S8Packets OBJECT-TYPE
	SYNTAX		Counter64
	MAX-ACCESS read-only
	STATUS		current
	DESCRIPTION
		"Aggregated number of uplink packet received for HE MCS10 8 Spatial Streams
		Device Allocation: AP"
	::= { ulWlanHEMCSPackets 95 }

ulWLanHEMCS11S8Packets OBJECT-TYPE
	SYNTAX		Counter64
	MAX-ACCESS read-only
	STATUS		current
	DESCRIPTION
		"Aggregated number of uplink packet received for HE MCS11 8 Spatial Streams
		Device Allocation: AP"
	::= { ulWlanHEMCSPackets 96 }

ulWLanHEMCS12S1Packets OBJECT-TYPE
	SYNTAX		Counter64
	MAX-ACCESS read-only
	STATUS		current
	DESCRIPTION
		"Aggregated number of uplink packet received for HE MCS12 1 Spatial Streams
		Device Allocation: AP"
	::= { ulWlanHEMCSPackets 97 }

ulWLanHEMCS13S1Packets OBJECT-TYPE
	SYNTAX		Counter64
	MAX-ACCESS read-only
	STATUS		current
	DESCRIPTION
		"Aggregated number of uplink packet received for HE MCS13 1 Spatial Streams
		Device Allocation: AP"
	::= { ulWlanHEMCSPackets 98 }

ulWLanHEMCS12S2Packets OBJECT-TYPE
	SYNTAX		Counter64
	MAX-ACCESS read-only
	STATUS		current
	DESCRIPTION
		"Aggregated number of uplink packet received for HE MCS12 2 Spatial Streams
		Device Allocation: AP"
	::= { ulWlanHEMCSPackets 99 }

ulWLanHEMCS13S2Packets OBJECT-TYPE
	SYNTAX		Counter64
	MAX-ACCESS read-only
	STATUS		current
	DESCRIPTION
		"Aggregated number of uplink packet received for HE MCS13 2 Spatial Streams
		Device Allocation: AP"
	::= { ulWlanHEMCSPackets 100 }

ulWLanHEMCS12S3Packets OBJECT-TYPE
	SYNTAX		Counter64
	MAX-ACCESS read-only
	STATUS		current
	DESCRIPTION
		"Aggregated number of uplink packet received for HE MCS12 3 Spatial Streams
		Device Allocation: AP"
	::= { ulWlanHEMCSPackets 101 }

ulWLanHEMCS13S3Packets OBJECT-TYPE
	SYNTAX		Counter64
	MAX-ACCESS read-only
	STATUS		current
	DESCRIPTION
		"Aggregated number of uplink packet received for HE MCS13 3 Spatial Streams
		Device Allocation: AP"
	::= { ulWlanHEMCSPackets 102 }

ulWLanHEMCS12S4Packets OBJECT-TYPE
	SYNTAX		Counter64
	MAX-ACCESS read-only
	STATUS		current
	DESCRIPTION
		"Aggregated number of uplink packet received for HE MCS12 4 Spatial Streams
		Device Allocation: AP"
	::= { ulWlanHEMCSPackets 103 }

ulWLanHEMCS13S4Packets OBJECT-TYPE
	SYNTAX		Counter64
	MAX-ACCESS read-only
	STATUS		current
	DESCRIPTION
		"Aggregated number of uplink packet received for HE MCS13 4 Spatial Streams
		Device Allocation: AP"
	::= { ulWlanHEMCSPackets 104 }

ulWLanHEMCS12S5Packets OBJECT-TYPE
	SYNTAX		Counter64
	MAX-ACCESS read-only
	STATUS		current
	DESCRIPTION
		"Aggregated number of uplink packet received for HE MCS12 5 Spatial Streams
		Device Allocation: AP"
	::= { ulWlanHEMCSPackets 105 }

ulWLanHEMCS13S5Packets OBJECT-TYPE
	SYNTAX		Counter64
	MAX-ACCESS read-only
	STATUS		current
	DESCRIPTION
		"Aggregated number of uplink packet received for HE MCS13 5 Spatial Streams
		Device Allocation: AP"
	::= { ulWlanHEMCSPackets 106 }

ulWLanHEMCS12S6Packets OBJECT-TYPE
	SYNTAX		Counter64
	MAX-ACCESS read-only
	STATUS		current
	DESCRIPTION
		"Aggregated number of uplink packet received for HE MCS12 6 Spatial Streams
		Device Allocation: AP"
	::= { ulWlanHEMCSPackets 107 }

ulWLanHEMCS13S6Packets OBJECT-TYPE
	SYNTAX		Counter64
	MAX-ACCESS read-only
	STATUS		current
	DESCRIPTION
		"Aggregated number of uplink packet received for HE MCS13 6 Spatial Streams
		Device Allocation: AP"
	::= { ulWlanHEMCSPackets 108 }

ulWLanHEMCS12S7Packets OBJECT-TYPE
	SYNTAX		Counter64
	MAX-ACCESS read-only
	STATUS		current
	DESCRIPTION
		"Aggregated number of uplink packet received for HE MCS12 7 Spatial Streams
		Device Allocation: AP"
	::= { ulWlanHEMCSPackets 109 }

ulWLanHEMCS13S7Packets OBJECT-TYPE
	SYNTAX		Counter64
	MAX-ACCESS read-only
	STATUS		current
	DESCRIPTION
		"Aggregated number of uplink packet received for HE MCS13 7 Spatial Streams
		Device Allocation: AP"
	::= { ulWlanHEMCSPackets 110 }

ulWLanHEMCS12S8Packets OBJECT-TYPE
	SYNTAX		Counter64
	MAX-ACCESS read-only
	STATUS		current
	DESCRIPTION
		"Aggregated number of uplink packet received for HE MCS12 8 Spatial Streams
		Device Allocation: AP"
	::= { ulWlanHEMCSPackets 111 }

ulWLanHEMCS13S8Packets OBJECT-TYPE
	SYNTAX		Counter64
	MAX-ACCESS read-only
	STATUS		current
	DESCRIPTION
		"Aggregated number of uplink packet received for HE MCS13 8 Spatial Streams
		Device Allocation: AP"
	::= { ulWlanHEMCSPackets 112 }

ulWLan2KbitCount OBJECT-TYPE
	SYNTAX	   Counter64
	MAX-ACCESS read-only
	STATUS	   current
	DESCRIPTION
		"Second Radio Aggregated total Uplink data traffic in kilobits
		Device Allocation: AP, SM"
	::= { cambiumPerformanceMonitoring 237 }

dlWLan2KbitCount OBJECT-TYPE
	SYNTAX	   Counter64
	MAX-ACCESS read-only
	STATUS	   current
	DESCRIPTION
		"Second Radio Aggregated total Downlink data traffic in kilobits
		Device Allocation: AP, SM"
	::= { cambiumPerformanceMonitoring 238 }

ulWLan2TotalPacketCount OBJECT-TYPE
	SYNTAX	   Counter64
	MAX-ACCESS read-only
	STATUS	   current
	DESCRIPTION
		"Second Radio Aggregated number of total Uplink data packet transmitted by
		SM or received by AP
		Device Allocation: AP, SM"
	::= { cambiumPerformanceMonitoring 239 }

dlWLan2TotalPacketCount OBJECT-TYPE
	SYNTAX	   Counter64
	MAX-ACCESS read-only
	STATUS	   current
	DESCRIPTION
		"Second Radio Aggregated number of total Downlink data packet transmitted by
		AP or received by SM
		Device Allocation: AP, SM"
	::= { cambiumPerformanceMonitoring 242 }

ulWLan2MultiBroadcastKbitCount OBJECT-TYPE
	SYNTAX	   Counter64
	MAX-ACCESS read-only
	STATUS	   current
	DESCRIPTION
		"Second Radio Aggregated total Uplink multicast and broadcast data traffic in
		kilobits
		Device Allocation: AP, SM"
	::= { cambiumPerformanceMonitoring 243 }

dlWLan2MultiBroadcastKbitCount OBJECT-TYPE
	SYNTAX	   Counter64
	MAX-ACCESS read-only
	STATUS	   current
	DESCRIPTION
		"Second Radio Aggregated total Downlink multicast and broadcast data traffic
		in kilobits
		Device Allocation: AP, SM"
	::= { cambiumPerformanceMonitoring 244 }

wLan2SessionDroppedCount OBJECT-TYPE
	SYNTAX	   Counter32
	MAX-ACCESS read-only
	STATUS	   current
	DESCRIPTION
		"Second Radio Aggregated number of SM session dropped due to no responses of
		bandwidth request response
		Device Allocation: AP, SM"
	::= { cambiumPerformanceMonitoring 245 }

ulWLan2ErrorDroppedPacketCount OBJECT-TYPE
	SYNTAX	   Counter64
	MAX-ACCESS read-only
	STATUS	   current
	DESCRIPTION
		"Second Radio Aggregated number of total Uplink data packet dropped due to
		data integrity error or other data packet association or RF
		error in packet
		Device Allocation: AP, SM"
	::= { cambiumPerformanceMonitoring 247 }

dlWLan2ErrorDroppedPacketCount OBJECT-TYPE
	SYNTAX	   Counter64
	MAX-ACCESS read-only
	STATUS	   current
	DESCRIPTION
		"Second Radio Aggregated number of total Downlink data packet dropped due to
		data integrity error or other data packet association error in
		packet
		Device Allocation: AP, SM"
	::= { cambiumPerformanceMonitoring 248 }

ulWLan2CapacityDroppedPacketCount OBJECT-TYPE
	SYNTAX	   Counter64
	MAX-ACCESS read-only
	STATUS	   current
	DESCRIPTION
		"Second Radio Aggregated number of total Uplink data packet dropped due to
		WLAN capacity issue in packets
		Device Allocation: AP, SM"
	::= { cambiumPerformanceMonitoring 249 }

dlWLan2CapacityDroppedPacketCount OBJECT-TYPE
	SYNTAX	   Counter64
	MAX-ACCESS read-only
	STATUS	   current
	DESCRIPTION
		"Second Radio Aggregated number of total Downlink data packet dropped due to
		exceed data buffer, over capacity or internal packet package
		sent issues in packet
		Device Allocation: AP, SM"
	::= { cambiumPerformanceMonitoring 250 }

ulWLan2TotalAvailableFrameTimePerSecond OBJECT-TYPE
	SYNTAX	   Integer32
	MAX-ACCESS read-only
	STATUS	   current
	DESCRIPTION
		"Second Radio Aggregated number of total uplink available frame time can be
		scheduled for traffic in micro second for 1 second period
		Device Allocation: AP"
	::= { cambiumPerformanceMonitoring 251 }

dlWLan2TotalAvailableFrameTimePerSecond OBJECT-TYPE
	SYNTAX	   Integer32
	MAX-ACCESS read-only
	STATUS	   current
	DESCRIPTION
		"Second Radio Aggregated number of total downlink available frame time can be
		scheduled for traffic in micro second for 1 second period
		Device Allocation: AP"
	::= { cambiumPerformanceMonitoring 252 }

ulWLan2TotalUsedFrameTimePerSecond OBJECT-TYPE
	SYNTAX	   Integer32
	MAX-ACCESS read-only
	STATUS	   current
	DESCRIPTION
		"Second Radio Aggregated number of uplink frame time schedule to be used in
		microsecond for 1 second period
		Device Allocation: AP"
	::= { cambiumPerformanceMonitoring 253 }

dlWLan2TotalUsedFrameTimePerSecond OBJECT-TYPE
	SYNTAX	   Integer32
	MAX-ACCESS read-only
	STATUS	   current
	DESCRIPTION
		"Second Radio Aggregated number of downlink frame time scheduled to be used
		per frame for 1 second period
		Device Allocation: AP"
	::= { cambiumPerformanceMonitoring 254 }

ulWLan2TotalOverheadFrameTimePerSecond OBJECT-TYPE
	SYNTAX	   Integer32
	MAX-ACCESS read-only
	STATUS	   current
	DESCRIPTION
		"Second Radio Aggregated number of uplink frame time is used for overhead
		(preamble and inter-frame gap) in microsecond for 1 second
		period
		Device Allocation: AP"
	::= { cambiumPerformanceMonitoring 255 }

dlWLan2TotalOverheadFrameTimePerSecond OBJECT-TYPE
	SYNTAX	   Integer32
	MAX-ACCESS read-only
	STATUS	   current
	DESCRIPTION
		"Second Radio Aggregated number of downlink frame time is used for overhead
		(preamble ans inter-frame gap) per frame for 1 second period
		Device Allocation: AP"
	::= { cambiumPerformanceMonitoring 256 }

ulWLan2RetransPacketCount OBJECT-TYPE
	SYNTAX	   Counter64
	MAX-ACCESS read-only
	STATUS	   current
	DESCRIPTION
		"Second Radio Aggregated number of total Uplink data packet retransmitted due
		to no-acknowledgement.
		Device Allocation: SM"
	::= { cambiumPerformanceMonitoring 258 }

dlWLan2RetransPacketCount OBJECT-TYPE
	SYNTAX	   Counter64
	MAX-ACCESS read-only
	STATUS	   current
	DESCRIPTION
		"Second Radio Aggregated number of total Downlink data packet retransmitted
		due to no-acknowledgement
		Device Allocation: AP"
	::= { cambiumPerformanceMonitoring 259 }

ulWLan2BroadcastPacketCount OBJECT-TYPE
	SYNTAX	   Counter64
	MAX-ACCESS read-only
	STATUS	   current
	DESCRIPTION
		"Second Radio Aggregated total Uplink broadcast packet counter
		Device Allocation: AP, SM"
	::= { cambiumPerformanceMonitoring 260 }

dlWLan2BroadcastPacketCount OBJECT-TYPE
	SYNTAX	   Counter64
	MAX-ACCESS read-only
	STATUS	   current
	DESCRIPTION
		"Second Radio Aggregated total Downlink broadcast packet counter
		Device Allocation: AP, SM"
	::= { cambiumPerformanceMonitoring 261 }

ulWLan2MulticastPacketCount OBJECT-TYPE
	SYNTAX	   Counter64
	MAX-ACCESS read-only
	STATUS	   current
	DESCRIPTION
		"Second Radio Aggregated total Uplink multicast packet counter
		Device Allocation: AP, SM"
	::= { cambiumPerformanceMonitoring 262 }

dlWLan2MulticastPacketCount OBJECT-TYPE
	SYNTAX	   Counter64
	MAX-ACCESS read-only
	STATUS	   current
	DESCRIPTION
		"Second Radio Aggregated total Downlink multicast packet counter
		Device Allocation: AP, SM"
	::= { cambiumPerformanceMonitoring 263 }

rxEtherLan2KbitCount OBJECT-TYPE
	SYNTAX	   Counter64
	MAX-ACCESS read-only
	STATUS	   current
	DESCRIPTION
		"Second Port (SFP) Total Ethernet RX bytes
		Device Allocation: AP, SM"
	::= { cambiumPerformanceMonitoring 265 }

rxEtherLan2TotalPacketCount OBJECT-TYPE
	SYNTAX	   Counter64
	MAX-ACCESS read-only
	STATUS	   current
	DESCRIPTION
		"Second Port (SFP) Total Ethernet RX packets
		Device Allocation: AP, SM"
	::= { cambiumPerformanceMonitoring 266 }

rxEtherLan2ErrorPacketCount OBJECT-TYPE
	SYNTAX	   Counter64
	MAX-ACCESS read-only
	STATUS	   current
	DESCRIPTION
		"Second Port (SFP) Total Ethernet RX errors
		Device Allocation: AP, SM"
	::= { cambiumPerformanceMonitoring 267 }

rxEtherLan2DroppedPacketCount OBJECT-TYPE
	SYNTAX	   Counter64
	MAX-ACCESS read-only
	STATUS	   current
	DESCRIPTION
		"Second Port (SFP) Total Ethernet RX drops
		Device Allocation: AP, SM"
	::= { cambiumPerformanceMonitoring 268 }

rxEtherLan2MulticastPacketCount OBJECT-TYPE
	SYNTAX	   Counter64
	MAX-ACCESS read-only
	STATUS	   current
	DESCRIPTION
		"Second Port (SFP) Total Ethernet RX multicast
		Device Allocation: AP, SM"
	::= { cambiumPerformanceMonitoring 269 }

rxEtherLan2BroadcastPacketCount OBJECT-TYPE
	SYNTAX	   Counter64
	MAX-ACCESS read-only
	STATUS	   current
	DESCRIPTION
		"Second Port (SFP) Total Ethernet RX broadcast
		Device Allocation: AP, SM"
	::= { cambiumPerformanceMonitoring 270 }

rxEtherLan2MultiBroadcastKbitCount OBJECT-TYPE
	SYNTAX	   Counter64
	MAX-ACCESS read-only
	STATUS	   current
	DESCRIPTION
		"Second Port (SFP) Aggregated total Ethernet RX multicast and broadcast data traffic
		Device Allocation: AP, SM"
	::= { cambiumPerformanceMonitoring 271 }

txEtherLan2KbitCount OBJECT-TYPE
	SYNTAX	   Counter64
	MAX-ACCESS read-only
	STATUS	   current
	DESCRIPTION
		"Second Port (SFP) Total Ethernet TX bytes
		Device Allocation: AP, SM"
	::= { cambiumPerformanceMonitoring 272 }

txEtherLan2TotalPacketCount OBJECT-TYPE
	SYNTAX	   Counter64
	MAX-ACCESS read-only
	STATUS	   current
	DESCRIPTION
		"Second Port (SFP) Total Ethernet TX packets
		Device Allocation: AP, SM"
	::= { cambiumPerformanceMonitoring 273 }

txEtherLan2ErrorPacketCount OBJECT-TYPE
	SYNTAX	   Counter64
	MAX-ACCESS read-only
	STATUS	   current
	DESCRIPTION
		"Second Port (SFP) Total Ethernet TX errors
		Device Allocation: AP, SM"
	::= { cambiumPerformanceMonitoring 274 }

txEtherLan2DroppedPacketCount OBJECT-TYPE
	SYNTAX	   Counter64
	MAX-ACCESS read-only
	STATUS	   current
	DESCRIPTION
		"Second Port (SFP) Total Ethernet TX drops
		Device Allocation: AP, SM"
	::= { cambiumPerformanceMonitoring 275 }

txEtherLan2MulticastPacketCount OBJECT-TYPE
	SYNTAX	   Counter64
	MAX-ACCESS read-only
	STATUS	   current
	DESCRIPTION
		"Second Port (SFP) Total Ethernet TX multicast
		Device Allocation: AP, SM"
	::= { cambiumPerformanceMonitoring 276 }

txEtherLan2BroadcastPacketCount OBJECT-TYPE
	SYNTAX	   Counter64
	MAX-ACCESS read-only
	STATUS	   current
	DESCRIPTION
		"Second Port (SFP) Total Ethernet TX broadcast
		Device Allocation: AP, SM"
	::= { cambiumPerformanceMonitoring 277 }

txEtherLan2MultiBroadcastKbitCount OBJECT-TYPE
	SYNTAX	   Counter64
	MAX-ACCESS read-only
	STATUS	   current
	DESCRIPTION
		"Second Port (SFP) Aggregated total Ethernet TX multicast and broadcast data traffic
		Device Allocation: AP, SM"
	::= { cambiumPerformanceMonitoring 278 }

ulWLan2TotalAvailableFrameTimePercentage OBJECT-TYPE
	SYNTAX     Integer32
	MAX-ACCESS read-only
	STATUS     current
	DESCRIPTION
		"Second Radio Aggregated uplink frame 10X percentage time
		Range = [1..1000] 0.1% = 1; 100% = 1000
		Device Allocation: AP"
	::= { cambiumPerformanceMonitoring 312 }

dlWLan2TotalAvailableFrameTimePercentage OBJECT-TYPE
	SYNTAX     Integer32
	MAX-ACCESS read-only
	STATUS     current
	DESCRIPTION
		"Second Radio Aggregated downlink frame 10X percentage time
		Range = [1..1000] 0.1% = 1; 100% = 1000
		Device Allocation: AP"
	::= { cambiumPerformanceMonitoring 313 }

ulWLan2VHTMCS0SSPackets OBJECT-TYPE
	SYNTAX	   Counter64
	MAX-ACCESS read-only
	STATUS	   current
	DESCRIPTION
		"Second Radio Aggregated number of uplink packet received for VHT MCS0 Single Stream
		Device Allocation: AP"
	::= { cambiumPerformanceMonitoring 330 }

ulWLan2VHTMCS1SSPackets OBJECT-TYPE
	SYNTAX	   Counter64
	MAX-ACCESS read-only
	STATUS	   current
	DESCRIPTION
		"Second Radio Aggregated number of uplink packet received for VHT MCS1 Single Stream
		Device Allocation: AP"
	::= { cambiumPerformanceMonitoring 331 }

ulWLan2VHTMCS2SSPackets OBJECT-TYPE
	SYNTAX	   Counter64
	MAX-ACCESS read-only
	STATUS	   current
	DESCRIPTION
		"Second Radio Aggregated number of uplink packet received for VHT MCS2 Single Stream
		Device Allocation: AP"
	::= { cambiumPerformanceMonitoring 332 }

ulWLan2VHTMCS3SSPackets OBJECT-TYPE
	SYNTAX	   Counter64
	MAX-ACCESS read-only
	STATUS	   current
	DESCRIPTION
		"Second Radio Aggregated number of uplink packet received for VHT MCS3 Single Stream
		Device Allocation: AP"
	::= { cambiumPerformanceMonitoring 333 }

ulWLan2VHTMCS4SSPackets OBJECT-TYPE
	SYNTAX	   Counter64
	MAX-ACCESS read-only
	STATUS	   current
	DESCRIPTION
		"Second Radio Aggregated number of uplink packet received for VHT MCS4 Single Stream
		Device Allocation: AP"
	::= { cambiumPerformanceMonitoring 334 }

ulWLan2VHTMCS5SSPackets OBJECT-TYPE
	SYNTAX	   Counter64
	MAX-ACCESS read-only
	STATUS	   current
	DESCRIPTION
		"Second Radio Aggregated number of uplink packet received for VHT MCS5 Single Stream
		Device Allocation: AP"
	::= { cambiumPerformanceMonitoring 335 }

ulWLan2VHTMCS6SSPackets OBJECT-TYPE
	SYNTAX	   Counter64
	MAX-ACCESS read-only
	STATUS	   current
	DESCRIPTION
		"Second Radio Aggregated number of uplink packet received for VHT MCS6 Single Stream
		Device Allocation: AP"
	::= { cambiumPerformanceMonitoring 336 }

ulWLan2VHTMCS7SSPackets OBJECT-TYPE
	SYNTAX	   Counter64
	MAX-ACCESS read-only
	STATUS	   current
	DESCRIPTION
		"Second Radio Aggregated number of uplink packet received for VHT MCS7 Single Stream
		Device Allocation: AP"
	::= { cambiumPerformanceMonitoring 337 }

ulWLan2VHTMCS8SSPackets OBJECT-TYPE
	SYNTAX	   Counter64
	MAX-ACCESS read-only
	STATUS	   current
	DESCRIPTION
		"Second Radio Aggregated number of uplink packet received for VHT MCS8 Single Stream
		Device Allocation: AP"
	::= { cambiumPerformanceMonitoring 338 }

ulWLan2VHTMCS9SSPackets OBJECT-TYPE
	SYNTAX	   Counter64
	MAX-ACCESS read-only
	STATUS	   current
	DESCRIPTION
		"Second Radio Aggregated number of uplink packet received for VHT MCS9 Single Stream
		Device Allocation: AP"
	::= { cambiumPerformanceMonitoring 339 }

ulWLan2VHTMCS0DSPackets OBJECT-TYPE
	SYNTAX	   Counter64
	MAX-ACCESS read-only
	STATUS	   current
	DESCRIPTION
		"Second Radio Aggregated number of uplink packet received for VHT MCS0 Dual Stream
		Device Allocation: AP"
	::= { cambiumPerformanceMonitoring 340 }

ulWLan2VHTMCS1DSPackets OBJECT-TYPE
	SYNTAX	   Counter64
	MAX-ACCESS read-only
	STATUS	   current
	DESCRIPTION
		"Second Radio Aggregated number of uplink packet received for VHT MCS1 Dual Stream
		Device Allocation: AP"
	::= { cambiumPerformanceMonitoring 341 }

ulWLan2VHTMCS2DSPackets OBJECT-TYPE
	SYNTAX	   Counter64
	MAX-ACCESS read-only
	STATUS	   current
	DESCRIPTION
		"Second Radio Aggregated number of uplink packet received for VHT MCS2 Dual Stream
		Device Allocation: AP"
	::= { cambiumPerformanceMonitoring 342 }

ulWLan2VHTMCS3DSPackets OBJECT-TYPE
	SYNTAX	   Counter64
	MAX-ACCESS read-only
	STATUS	   current
	DESCRIPTION
		"Second Radio Aggregated number of uplink packet received for VHT MCS3 Dual Stream
		Device Allocation: AP"
	::= { cambiumPerformanceMonitoring 343 }

ulWLan2VHTMCS4DSPackets OBJECT-TYPE
	SYNTAX	   Counter64
	MAX-ACCESS read-only
	STATUS	   current
	DESCRIPTION
		"Second Radio Aggregated number of uplink packet received for VHT MCS4 Dual Stream
		Device Allocation: AP"
	::= { cambiumPerformanceMonitoring 344 }

ulWLan2VHTMCS5DSPackets OBJECT-TYPE
	SYNTAX	   Counter64
	MAX-ACCESS read-only
	STATUS	   current
	DESCRIPTION
		"Second Radio Aggregated number of uplink packet received for VHT MCS5 Dual Stream
		Device Allocation: AP"
	::= { cambiumPerformanceMonitoring 345 }

ulWLan2VHTMCS6DSPackets OBJECT-TYPE
	SYNTAX	   Counter64
	MAX-ACCESS read-only
	STATUS	   current
	DESCRIPTION
		"Second Radio Aggregated number of uplink packet received for VHT MCS6 Dual Stream
		Device Allocation: AP"
	::= { cambiumPerformanceMonitoring 346 }

ulWLan2VHTMCS7DSPackets OBJECT-TYPE
	SYNTAX	   Counter64
	MAX-ACCESS read-only
	STATUS	   current
	DESCRIPTION
		"Second Radio Aggregated number of uplink packet received for VHT MCS7 Dual Stream
		Device Allocation: AP"
	::= { cambiumPerformanceMonitoring 347 }

ulWLan2VHTMCS8DSPackets OBJECT-TYPE
	SYNTAX	   Counter64
	MAX-ACCESS read-only
	STATUS	   current
	DESCRIPTION
		"Second Radio Aggregated number of uplink packet received for VHT MCS8 Dual Stream
		Device Allocation: AP"
	::= { cambiumPerformanceMonitoring 348 }

ulWLan2VHTMCS9DSPackets OBJECT-TYPE
	SYNTAX	   Counter64
	MAX-ACCESS read-only
	STATUS	   current
	DESCRIPTION
		"Second Radio Aggregated number of uplink packet received for VHT MCS9 Dual Stream
		Device Allocation: AP"
	::= { cambiumPerformanceMonitoring 349 }

dlWLan2VHTMCS0SSPackets OBJECT-TYPE
	SYNTAX	   Counter64
	MAX-ACCESS read-only
	STATUS	   current
	DESCRIPTION
		"Second Radio Aggregated number of downlink packet received for VHT MCS0 Single Stream
		Device Allocation: AP"
	::= { cambiumPerformanceMonitoring 350 }

dlWLan2VHTMCS1SSPackets OBJECT-TYPE
	SYNTAX	   Counter64
	MAX-ACCESS read-only
	STATUS	   current
	DESCRIPTION
		"Second Radio Aggregated number of downlink packet received for VHT MCS1 Single Stream
		Device Allocation: AP"
	::= { cambiumPerformanceMonitoring 351 }

dlWLan2VHTMCS2SSPackets OBJECT-TYPE
	SYNTAX	   Counter64
	MAX-ACCESS read-only
	STATUS	   current
	DESCRIPTION
		"Second Radio Aggregated number of downlink packet received for VHT MCS2 Single Stream
		Device Allocation: AP"
	::= { cambiumPerformanceMonitoring 352 }

dlWLan2VHTMCS3SSPackets OBJECT-TYPE
	SYNTAX	   Counter64
	MAX-ACCESS read-only
	STATUS	   current
	DESCRIPTION
		"Second Radio Aggregated number of downlink packet received for VHT MCS3 Single Stream
		Device Allocation: AP"
	::= { cambiumPerformanceMonitoring 353 }

dlWLan2VHTMCS4SSPackets OBJECT-TYPE
	SYNTAX	   Counter64
	MAX-ACCESS read-only
	STATUS	   current
	DESCRIPTION
		"Second Radio Aggregated number of downlink packet received for VHT MCS4 Single Stream
		Device Allocation: AP"
	::= { cambiumPerformanceMonitoring 354 }

dlWLan2VHTMCS5SSPackets OBJECT-TYPE
	SYNTAX	   Counter64
	MAX-ACCESS read-only
	STATUS	   current
	DESCRIPTION
		"Second Radio Aggregated number of downlink packet received for VHT MCS5 Single Stream
		Device Allocation: AP"
	::= { cambiumPerformanceMonitoring 355 }

dlWLan2VHTMCS6SSPackets OBJECT-TYPE
	SYNTAX	   Counter64
	MAX-ACCESS read-only
	STATUS	   current
	DESCRIPTION
		"Second Radio Aggregated number of downlink packet received for VHT MCS6 Single Stream
		Device Allocation: AP"
	::= { cambiumPerformanceMonitoring 356 }

dlWLan2VHTMCS7SSPackets OBJECT-TYPE
	SYNTAX	   Counter64
	MAX-ACCESS read-only
	STATUS	   current
	DESCRIPTION
		"Second Radio Aggregated number of downlink packet received for VHT MCS7 Single Stream
		Device Allocation: AP"
	::= { cambiumPerformanceMonitoring 357 }

dlWLan2VHTMCS8SSPackets OBJECT-TYPE
	SYNTAX	   Counter64
	MAX-ACCESS read-only
	STATUS	   current
	DESCRIPTION
		"Second Radio Aggregated number of downlink packet received for VHT MCS8 Single Stream
		Device Allocation: AP"
	::= { cambiumPerformanceMonitoring 358 }

dlWLan2VHTMCS9SSPackets OBJECT-TYPE
	SYNTAX	   Counter64
	MAX-ACCESS read-only
	STATUS	   current
	DESCRIPTION
		"Second Radio Aggregated number of downlink packet received for VHT MCS9 Single Stream
		Device Allocation: AP"
	::= { cambiumPerformanceMonitoring 359 }

dlWLan2VHTMCS0DSPackets OBJECT-TYPE
	SYNTAX	   Counter64
	MAX-ACCESS read-only
	STATUS	   current
	DESCRIPTION
		"Second Radio Aggregated number of downlink packet received for VHT MCS0 Dual Stream
		Device Allocation: AP"
	::= { cambiumPerformanceMonitoring 360 }

dlWLan2VHTMCS1DSPackets OBJECT-TYPE
	SYNTAX	   Counter64
	MAX-ACCESS read-only
	STATUS	   current
	DESCRIPTION
		"Second Radio Aggregated number of downlink packet received for VHT MCS1 Dual Stream
		Device Allocation: AP"
	::= { cambiumPerformanceMonitoring 361 }

dlWLan2VHTMCS2DSPackets OBJECT-TYPE
	SYNTAX	   Counter64
	MAX-ACCESS read-only
	STATUS	   current
	DESCRIPTION
		"Second Radio Aggregated number of downlink packet received for VHT MCS2 Dual Stream
		Device Allocation: AP"
	::= { cambiumPerformanceMonitoring 362 }

dlWLan2VHTMCS3DSPackets OBJECT-TYPE
	SYNTAX	   Counter64
	MAX-ACCESS read-only
	STATUS	   current
	DESCRIPTION
		"Second Radio Aggregated number of downlink packet received for VHT MCS3 Dual Stream
		Device Allocation: AP"
	::= { cambiumPerformanceMonitoring 363 }

dlWLan2VHTMCS4DSPackets OBJECT-TYPE
	SYNTAX	   Counter64
	MAX-ACCESS read-only
	STATUS	   current
	DESCRIPTION
		"Second Radio Aggregated number of downlink packet received for VHT MCS4 Dual Stream
		Device Allocation: AP"
	::= { cambiumPerformanceMonitoring 364 }

dlWLan2VHTMCS5DSPackets OBJECT-TYPE
	SYNTAX	   Counter64
	MAX-ACCESS read-only
	STATUS	   current
	DESCRIPTION
		"Second Radio Aggregated number of downlink packet received for VHT MCS5 Dual Stream
		Device Allocation: AP"
	::= { cambiumPerformanceMonitoring 365 }

dlWLan2VHTMCS6DSPackets OBJECT-TYPE
	SYNTAX	   Counter64
	MAX-ACCESS read-only
	STATUS	   current
	DESCRIPTION
		"Second Radio Aggregated number of downlink packet received for VHT MCS6 Dual Stream
		Device Allocation: AP"
	::= { cambiumPerformanceMonitoring 366 }

dlWLan2VHTMCS7DSPackets OBJECT-TYPE
	SYNTAX	   Counter64
	MAX-ACCESS read-only
	STATUS	   current
	DESCRIPTION
		"Second Radio Aggregated number of downlink packet received for VHT MCS7 Dual Stream
		Device Allocation: AP"
	::= { cambiumPerformanceMonitoring 367 }

dlWLan2VHTMCS8DSPackets OBJECT-TYPE
	SYNTAX	   Counter64
	MAX-ACCESS read-only
	STATUS	   current
	DESCRIPTION
		"Second Radio Aggregated number of downlink packet received for VHT MCS8 Dual Stream
		Device Allocation: AP"
	::= { cambiumPerformanceMonitoring 368 }

dlWLan2VHTMCS9DSPackets OBJECT-TYPE
	SYNTAX	   Counter64
	MAX-ACCESS read-only
	STATUS	   current
	DESCRIPTION
		"Second Radio Aggregated number of downlink packet received for VHT MCS9 Dual Stream
		Device Allocation: AP"
	::= { cambiumPerformanceMonitoring 369 }

wLan2SNRDeviation00Cnt OBJECT-TYPE
	SYNTAX	   Counter64
	MAX-ACCESS read-only
	STATUS	   current
	DESCRIPTION
		"Second radio Number of deviations from average SNR with absolute value 00
		Device Allocation: AP, SM"
	::= { cambiumPerformanceMonitoring 370 }

wLan2SNRDeviation01Cnt OBJECT-TYPE
	SYNTAX	   Counter64
	MAX-ACCESS read-only
	STATUS	   current
	DESCRIPTION
		"Second radio Number of deviations from average SNR with absolute value 01
		Device Allocation: AP, SM"
	::= { cambiumPerformanceMonitoring 371 }

wLan2SNRDeviation02Cnt OBJECT-TYPE
	SYNTAX	   Counter64
	MAX-ACCESS read-only
	STATUS	   current
	DESCRIPTION
		"Second radio Number of deviations from average SNR with absolute value 02
		Device Allocation: AP, SM"
	::= { cambiumPerformanceMonitoring 372 }

wLan2SNRDeviation03Cnt OBJECT-TYPE
	SYNTAX	   Counter64
	MAX-ACCESS read-only
	STATUS	   current
	DESCRIPTION
		"Second radio Number of deviations from average SNR with absolute value 03
		Device Allocation: AP, SM"
	::= { cambiumPerformanceMonitoring 373 }

wLan2SNRDeviation04Cnt OBJECT-TYPE
	SYNTAX	   Counter64
	MAX-ACCESS read-only
	STATUS	   current
	DESCRIPTION
		"Second radio Number of deviations from average SNR with absolute value 04
		Device Allocation: AP, SM"
	::= { cambiumPerformanceMonitoring 374 }

wLan2SNRDeviation05Cnt OBJECT-TYPE
	SYNTAX	   Counter64
	MAX-ACCESS read-only
	STATUS	   current
	DESCRIPTION
		"Second radio Number of deviations from average SNR with absolute value 05
		Device Allocation: AP, SM"
	::= { cambiumPerformanceMonitoring 375 }

wLan2SNRDeviation06Cnt OBJECT-TYPE
	SYNTAX	   Counter64
	MAX-ACCESS read-only
	STATUS	   current
	DESCRIPTION
		"Second radio Number of deviations from average SNR with absolute value 06
		Device Allocation: AP, SM"
	::= { cambiumPerformanceMonitoring 376 }

wLan2SNRDeviation07Cnt OBJECT-TYPE
	SYNTAX	   Counter64
	MAX-ACCESS read-only
	STATUS	   current
	DESCRIPTION
		"Second radio Number of deviations from average SNR with absolute value 07
		Device Allocation: AP, SM"
	::= { cambiumPerformanceMonitoring 377 }

wLan2SNRDeviation08Cnt OBJECT-TYPE
	SYNTAX	   Counter64
	MAX-ACCESS read-only
	STATUS	   current
	DESCRIPTION
		"Second radio Number of deviations from average SNR with absolute value 08
		Device Allocation: AP, SM"
	::= { cambiumPerformanceMonitoring 378 }

wLan2SNRDeviation09Cnt OBJECT-TYPE
	SYNTAX	   Counter64
	MAX-ACCESS read-only
	STATUS	   current
	DESCRIPTION
		"Second radio Number of deviations from average SNR with absolute value 09
		Device Allocation: AP, SM"
	::= { cambiumPerformanceMonitoring 379 }

wLan2SNRDeviation10Cnt OBJECT-TYPE
	SYNTAX	   Counter64
	MAX-ACCESS read-only
	STATUS	   current
	DESCRIPTION
		"Second radio Number of deviations from average SNR with absolute value 10
		Device Allocation: AP, SM"
	::= { cambiumPerformanceMonitoring 380 }

wLan2SNRDeviation11Cnt OBJECT-TYPE
	SYNTAX	   Counter64
	MAX-ACCESS read-only
	STATUS	   current
	DESCRIPTION
		"Second radio Number of deviations from average SNR with absolute value 11
		Device Allocation: AP, SM"
	::= { cambiumPerformanceMonitoring 381 }

wLan2SNRDeviation12Cnt OBJECT-TYPE
	SYNTAX	   Counter64
	MAX-ACCESS read-only
	STATUS	   current
	DESCRIPTION
		"Second radio Number of deviations from average SNR with absolute value 12
		Device Allocation: AP, SM"
	::= { cambiumPerformanceMonitoring 382 }

wLan2SNRDeviation13Cnt OBJECT-TYPE
	SYNTAX	   Counter64
	MAX-ACCESS read-only
	STATUS	   current
	DESCRIPTION
		"Second radio Number of deviations from average SNR with absolute value 13
		Device Allocation: AP, SM"
	::= { cambiumPerformanceMonitoring 383 }

wLan2SNRDeviation14Cnt OBJECT-TYPE
	SYNTAX	   Counter64
	MAX-ACCESS read-only
	STATUS	   current
	DESCRIPTION
		"Second radio Number of deviations from average SNR with absolute value 14
		Device Allocation: AP, SM"
	::= { cambiumPerformanceMonitoring 384 }

wLan2SNRDeviation15Cnt OBJECT-TYPE
	SYNTAX	   Counter64
	MAX-ACCESS read-only
	STATUS	   current
	DESCRIPTION
		"Second radio Number of deviations from average SNR with absolute value 15
		Device Allocation: AP, SM"
	::= { cambiumPerformanceMonitoring 385 }

wLan2SNRDeviation16Cnt OBJECT-TYPE
	SYNTAX	   Counter64
	MAX-ACCESS read-only
	STATUS	   current
	DESCRIPTION
		"Second radio Number of deviations from average SNR with absolute value 16
		Device Allocation: AP, SM"
	::= { cambiumPerformanceMonitoring 386 }

wLan2SNRDeviation17Cnt OBJECT-TYPE
	SYNTAX	   Counter64
	MAX-ACCESS read-only
	STATUS	   current
	DESCRIPTION
		"Second radio Number of deviations from average SNR with absolute value 17
		Device Allocation: AP, SM"
	::= { cambiumPerformanceMonitoring 387 }

wLan2SNRDeviation18Cnt OBJECT-TYPE
	SYNTAX	   Counter64
	MAX-ACCESS read-only
	STATUS	   current
	DESCRIPTION
		"Second radio Number of deviations from average SNR with absolute value 18
		Device Allocation: AP, SM"
	::= { cambiumPerformanceMonitoring 388 }

wLan2SNRDeviation19Cnt OBJECT-TYPE
	SYNTAX	   Counter64
	MAX-ACCESS read-only
	STATUS	   current
	DESCRIPTION
		"Second radio Number of deviations from average SNR with absolute value 19
		Device Allocation: AP, SM"
	::= { cambiumPerformanceMonitoring 389 }

dlWLanMCS00UnicastPackets OBJECT-TYPE
	SYNTAX	   Counter64
	MAX-ACCESS read-only
	STATUS	   current
	DESCRIPTION
		"Aggregated number of downlink unicast packet received for MCS00
		Device Allocation: AP"
	::= { wlanMCSPackets 1 }

dlWLanMCS01UnicastPackets OBJECT-TYPE
	SYNTAX	   Counter64
	MAX-ACCESS read-only
	STATUS	   current
	DESCRIPTION
		"Aggregated number of downlink unicast packet received for MCS01
		Device Allocation: AP"
	::= { wlanMCSPackets 2 }

dlWLanMCS02UnicastPackets OBJECT-TYPE
	SYNTAX	   Counter64
	MAX-ACCESS read-only
	STATUS	   current
	DESCRIPTION
		"Aggregated number of downlink unicast packet received for MCS02
		Device Allocation: AP"
	::= { wlanMCSPackets 3 }

dlWLanMCS03UnicastPackets OBJECT-TYPE
	SYNTAX	   Counter64
	MAX-ACCESS read-only
	STATUS	   current
	DESCRIPTION
		"Aggregated number of downlink unicast packet received for MCS03
		Device Allocation: AP"
	::= { wlanMCSPackets 4 }

dlWLanMCS04UnicastPackets OBJECT-TYPE
	SYNTAX	   Counter64
	MAX-ACCESS read-only
	STATUS	   current
	DESCRIPTION
		"Aggregated number of downlink unicast packet received for MCS04
		Device Allocation: AP"
	::= { wlanMCSPackets 5 }

dlWLanMCS05UnicastPackets OBJECT-TYPE
	SYNTAX	   Counter64
	MAX-ACCESS read-only
	STATUS	   current
	DESCRIPTION
		"Aggregated number of downlink unicast packet received for MCS05
		Device Allocation: AP"
	::= { wlanMCSPackets 6 }

dlWLanMCS06UnicastPackets OBJECT-TYPE
	SYNTAX	   Counter64
	MAX-ACCESS read-only
	STATUS	   current
	DESCRIPTION
		"Aggregated number of downlink unicast packet received for MCS06
		Device Allocation: AP"
	::= { wlanMCSPackets 7 }

dlWLanMCS07UnicastPackets OBJECT-TYPE
	SYNTAX	   Counter64
	MAX-ACCESS read-only
	STATUS	   current
	DESCRIPTION
		"Aggregated number of downlink unicast packet received for MCS07
		Device Allocation: AP"
	::= { wlanMCSPackets 8 }

dlWLanMCS08UnicastPackets OBJECT-TYPE
	SYNTAX	   Counter64
	MAX-ACCESS read-only
	STATUS	   current
	DESCRIPTION
		"Aggregated number of downlink unicast packet received for MCS08
		Device Allocation: AP"
	::= { wlanMCSPackets 9 }

dlWLanMCS09UnicastPackets OBJECT-TYPE
	SYNTAX	   Counter64
	MAX-ACCESS read-only
	STATUS	   current
	DESCRIPTION
		"Aggregated number of downlink unicast packet received for MCS09
		Device Allocation: AP"
	::= { wlanMCSPackets 10 }

dlWLanMCS10UnicastPackets OBJECT-TYPE
	SYNTAX	   Counter64
	MAX-ACCESS read-only
	STATUS	   current
	DESCRIPTION
		"Aggregated number of downlink unicast packet received for MCS10
		Device Allocation: AP"
	::= { wlanMCSPackets 11 }

dlWLanMCS11UnicastPackets OBJECT-TYPE
	SYNTAX	   Counter64
	MAX-ACCESS read-only
	STATUS	   current
	DESCRIPTION
		"Aggregated number of downlink unicast packet received for MCS11
		Device Allocation: AP"
	::= { wlanMCSPackets 12 }

dlWLanMCS12UnicastPackets OBJECT-TYPE
	SYNTAX	   Counter64
	MAX-ACCESS read-only
	STATUS	   current
	DESCRIPTION
		"Aggregated number of downlink unicast packet received for MCS12
		Device Allocation: AP"
	::= { wlanMCSPackets 13 }

dlWLanMCS13UnicastPackets OBJECT-TYPE
	SYNTAX	   Counter64
	MAX-ACCESS read-only
	STATUS	   current
	DESCRIPTION
		"Aggregated number of downlink unicast packet received for MCS13
		Device Allocation: AP"
	::= { wlanMCSPackets 14 }

dlWLanMCS14UnicastPackets OBJECT-TYPE
	SYNTAX	   Counter64
	MAX-ACCESS read-only
	STATUS	   current
	DESCRIPTION
		"Aggregated number of downlink unicast packet received for MCS14
		Device Allocation: AP"
	::= { wlanMCSPackets 15 }

dlWLanMCS15UnicastPackets OBJECT-TYPE
	SYNTAX	   Counter64
	MAX-ACCESS read-only
	STATUS	   current
	DESCRIPTION
		"Aggregated number of downlink unicast packet received for MCS15
		Device Allocation: AP"
	::= { wlanMCSPackets 16 }

ulWLanMCS00UnicastPackets OBJECT-TYPE
	SYNTAX	   Counter64
	MAX-ACCESS read-only
	STATUS	   current
	DESCRIPTION
		"Aggregated number of uplink unicast packet received for MCS00
		Device Allocation: AP"
	::= { wlanMCSPackets 17 }

ulWLanMCS01UnicastPackets OBJECT-TYPE
	SYNTAX	   Counter64
	MAX-ACCESS read-only
	STATUS	   current
	DESCRIPTION
		"Aggregated number of uplink unicast packet received for MCS01
		Device Allocation: AP"
	::= { wlanMCSPackets 18 }

ulWLanMCS02UnicastPackets OBJECT-TYPE
	SYNTAX	   Counter64
	MAX-ACCESS read-only
	STATUS	   current
	DESCRIPTION
		"Aggregated number of uplink unicast packet received for MCS02
		Device Allocation: AP"
	::= { wlanMCSPackets 19 }

ulWLanMCS03UnicastPackets OBJECT-TYPE
	SYNTAX	   Counter64
	MAX-ACCESS read-only
	STATUS	   current
	DESCRIPTION
		"Aggregated number of uplink unicast packet received for MCS03
		Device Allocation: AP"
	::= { wlanMCSPackets 20 }

ulWLanMCS04UnicastPackets OBJECT-TYPE
	SYNTAX	   Counter64
	MAX-ACCESS read-only
	STATUS	   current
	DESCRIPTION
		"Aggregated number of uplink unicast packet received for MCS04
		Device Allocation: AP"
	::= { wlanMCSPackets 21 }

ulWLanMCS05UnicastPackets OBJECT-TYPE
	SYNTAX	   Counter64
	MAX-ACCESS read-only
	STATUS	   current
	DESCRIPTION
		"Aggregated number of uplink unicast packet received for MCS05
		Device Allocation: AP"
	::= { wlanMCSPackets 22 }

ulWLanMCS06UnicastPackets OBJECT-TYPE
	SYNTAX	   Counter64
	MAX-ACCESS read-only
	STATUS	   current
	DESCRIPTION
		"Aggregated number of uplink unicast packet received for MCS06
		Device Allocation: AP"
	::= { wlanMCSPackets 23 }

ulWLanMCS07UnicastPackets OBJECT-TYPE
	SYNTAX	   Counter64
	MAX-ACCESS read-only
	STATUS	   current
	DESCRIPTION
		"Aggregated number of uplink unicast packet received for MCS07
		Device Allocation: AP"
	::= { wlanMCSPackets 24 }

ulWLanMCS08UnicastPackets OBJECT-TYPE
	SYNTAX	   Counter64
	MAX-ACCESS read-only
	STATUS	   current
	DESCRIPTION
		"Aggregated number of uplink unicast packet received for MCS08
		Device Allocation: AP"
	::= { wlanMCSPackets 25 }

ulWLanMCS09UnicastPackets OBJECT-TYPE
	SYNTAX	   Counter64
	MAX-ACCESS read-only
	STATUS	   current
	DESCRIPTION
		"Aggregated number of uplink unicast packet received for MCS09
		Device Allocation: AP"
	::= { wlanMCSPackets 26 }

ulWLanMCS10UnicastPackets OBJECT-TYPE
	SYNTAX	   Counter64
	MAX-ACCESS read-only
	STATUS	   current
	DESCRIPTION
		"Aggregated number of uplink unicast packet received for MCS10
		Device Allocation: AP"
	::= { wlanMCSPackets 27 }

ulWLanMCS11UnicastPackets OBJECT-TYPE
	SYNTAX	   Counter64
	MAX-ACCESS read-only
	STATUS	   current
	DESCRIPTION
		"Aggregated number of uplink unicast packet received for MCS11
		Device Allocation: AP"
	::= { wlanMCSPackets 28 }

ulWLanMCS12UnicastPackets OBJECT-TYPE
	SYNTAX	   Counter64
	MAX-ACCESS read-only
	STATUS	   current
	DESCRIPTION
		"Aggregated number of uplink unicast packet received for MCS12
		Device Allocation: AP"
	::= { wlanMCSPackets 29 }

ulWLanMCS13UnicastPackets OBJECT-TYPE
	SYNTAX	   Counter64
	MAX-ACCESS read-only
	STATUS	   current
	DESCRIPTION
		"Aggregated number of uplink unicast packet received for MCS13
		Device Allocation: AP"
	::= { wlanMCSPackets 30 }

ulWLanMCS14UnicastPackets OBJECT-TYPE
	SYNTAX	   Counter64
	MAX-ACCESS read-only
	STATUS	   current
	DESCRIPTION
		"Aggregated number of uplink unicast packet received for MCS14
		Device Allocation: AP"
	::= { wlanMCSPackets 31 }

ulWLanMCS15UnicastPackets OBJECT-TYPE
	SYNTAX	   Counter64
	MAX-ACCESS read-only
	STATUS	   current
	DESCRIPTION
		"Aggregated number of uplink unicast packet received for MCS15
		Device Allocation: AP"
	::= { wlanMCSPackets 32 }

dlWLanMCS00MulticastPackets OBJECT-TYPE
	SYNTAX	   Counter64
	MAX-ACCESS read-only
	STATUS	   current
	DESCRIPTION
		"Aggregated number of downlink multicast packet received for MCS00
		Device Allocation: AP"
	::= { wlanMCSPackets 33 }

dlWLanMCS01MulticastPackets OBJECT-TYPE
	SYNTAX	   Counter64
	MAX-ACCESS read-only
	STATUS	   current
	DESCRIPTION
		"Aggregated number of downlink multicast packet received for MCS01
		Device Allocation: AP"
	::= { wlanMCSPackets 34 }

dlWLanMCS02MulticastPackets OBJECT-TYPE
	SYNTAX	   Counter64
	MAX-ACCESS read-only
	STATUS	   current
	DESCRIPTION
		"Aggregated number of downlink multicast packet received for MCS02
		Device Allocation: AP"
	::= { wlanMCSPackets 35 }

dlWLanMCS03MulticastPackets OBJECT-TYPE
	SYNTAX	   Counter64
	MAX-ACCESS read-only
	STATUS	   current
	DESCRIPTION
		"Aggregated number of downlink multicast packet received for MCS03
		Device Allocation: AP"
	::= { wlanMCSPackets 36 }

dlWLanMCS04MulticastPackets OBJECT-TYPE
	SYNTAX	   Counter64
	MAX-ACCESS read-only
	STATUS	   current
	DESCRIPTION
		"Aggregated number of downlink multicast packet received for MCS04
		Device Allocation: AP"
	::= { wlanMCSPackets 37 }

dlWLanMCS05MulticastPackets OBJECT-TYPE
	SYNTAX	   Counter64
	MAX-ACCESS read-only
	STATUS	   current
	DESCRIPTION
		"Aggregated number of downlink multicast packet received for MCS05
		Device Allocation: AP"
	::= { wlanMCSPackets 38 }

dlWLanMCS06MulticastPackets OBJECT-TYPE
	SYNTAX	   Counter64
	MAX-ACCESS read-only
	STATUS	   current
	DESCRIPTION
		"Aggregated number of downlink multicast packet received for MCS06
		Device Allocation: AP"
	::= { wlanMCSPackets 39 }

dlWLanMCS07MulticastPackets OBJECT-TYPE
	SYNTAX	   Counter64
	MAX-ACCESS read-only
	STATUS	   current
	DESCRIPTION
		"Aggregated number of downlink multicast packet received for MCS07
		Device Allocation: AP"
	::= { wlanMCSPackets 40 }

dlWLanMCS08MulticastPackets OBJECT-TYPE
	SYNTAX	   Counter64
	MAX-ACCESS read-only
	STATUS	   current
	DESCRIPTION
		"Aggregated number of downlink multicast packet received for MCS08
		Device Allocation: AP"
	::= { wlanMCSPackets 41 }

dlWLanMCS09MulticastPackets OBJECT-TYPE
	SYNTAX	   Counter64
	MAX-ACCESS read-only
	STATUS	   current
	DESCRIPTION
		"Aggregated number of downlink multicast packet received for MCS09
		Device Allocation: AP"
	::= { wlanMCSPackets 42 }

dlWLanMCS10MulticastPackets OBJECT-TYPE
	SYNTAX	   Counter64
	MAX-ACCESS read-only
	STATUS	   current
	DESCRIPTION
		"Aggregated number of downlink multicast packet received for MCS10
		Device Allocation: AP"
	::= { wlanMCSPackets 43 }

dlWLanMCS11MulticastPackets OBJECT-TYPE
	SYNTAX	   Counter64
	MAX-ACCESS read-only
	STATUS	   current
	DESCRIPTION
		"Aggregated number of downlink multicast packet received for MCS11
		Device Allocation: AP"
	::= { wlanMCSPackets 44 }

dlWLanMCS12MulticastPackets OBJECT-TYPE
	SYNTAX	   Counter64
	MAX-ACCESS read-only
	STATUS	   current
	DESCRIPTION
		"Aggregated number of downlink multicast packet received for MCS12
		Device Allocation: AP"
	::= { wlanMCSPackets 45 }

dlWLanMCS13MulticastPackets OBJECT-TYPE
	SYNTAX	   Counter64
	MAX-ACCESS read-only
	STATUS	   current
	DESCRIPTION
		"Aggregated number of downlink multicast packet received for MCS13
		Device Allocation: AP"
	::= { wlanMCSPackets 46 }

dlWLanMCS14MulticastPackets OBJECT-TYPE
	SYNTAX	   Counter64
	MAX-ACCESS read-only
	STATUS	   current
	DESCRIPTION
		"Aggregated number of downlink multicast packet received for MCS14
		Device Allocation: AP"
	::= { wlanMCSPackets 47 }

dlWLanMCS15MulticastPackets OBJECT-TYPE
	SYNTAX	   Counter64
	MAX-ACCESS read-only
	STATUS	   current
	DESCRIPTION
		"Aggregated number of downlink multicast packet received for MCS15
		Device Allocation: AP"
	::= { wlanMCSPackets 48 }

ulWLanMCS00MulticastPackets OBJECT-TYPE
	SYNTAX	   Counter64
	MAX-ACCESS read-only
	STATUS	   current
	DESCRIPTION
		"Aggregated number of uplink multicast packet received for MCS00
		Device Allocation: AP"
	::= { wlanMCSPackets 49 }

ulWLanMCS01MulticastPackets OBJECT-TYPE
	SYNTAX	   Counter64
	MAX-ACCESS read-only
	STATUS	   current
	DESCRIPTION
		"Aggregated number of uplink multicast packet received for MCS01
		Device Allocation: AP"
	::= { wlanMCSPackets 50 }

ulWLanMCS02MulticastPackets OBJECT-TYPE
	SYNTAX	   Counter64
	MAX-ACCESS read-only
	STATUS	   current
	DESCRIPTION
		"Aggregated number of uplink multicast packet received for MCS02
		Device Allocation: AP"
	::= { wlanMCSPackets 51 }

ulWLanMCS03MulticastPackets OBJECT-TYPE
	SYNTAX	   Counter64
	MAX-ACCESS read-only
	STATUS	   current
	DESCRIPTION
		"Aggregated number of uplink multicast packet received for MCS03
		Device Allocation: AP"
	::= { wlanMCSPackets 52 }

ulWLanMCS04MulticastPackets OBJECT-TYPE
	SYNTAX	   Counter64
	MAX-ACCESS read-only
	STATUS	   current
	DESCRIPTION
		"Aggregated number of uplink multicast packet received for MCS04
		Device Allocation: AP"
	::= { wlanMCSPackets 53 }

ulWLanMCS05MulticastPackets OBJECT-TYPE
	SYNTAX	   Counter64
	MAX-ACCESS read-only
	STATUS	   current
	DESCRIPTION
		"Aggregated number of uplink multicast packet received for MCS05
		Device Allocation: AP"
	::= { wlanMCSPackets 54 }

ulWLanMCS06MulticastPackets OBJECT-TYPE
	SYNTAX	   Counter64
	MAX-ACCESS read-only
	STATUS	   current
	DESCRIPTION
		"Aggregated number of uplink multicast packet received for MCS06
		Device Allocation: AP"
	::= { wlanMCSPackets 55 }

ulWLanMCS07MulticastPackets OBJECT-TYPE
	SYNTAX	   Counter64
	MAX-ACCESS read-only
	STATUS	   current
	DESCRIPTION
		"Aggregated number of uplink multicast packet received for MCS07
		Device Allocation: AP"
	::= { wlanMCSPackets 56 }

ulWLanMCS08MulticastPackets OBJECT-TYPE
	SYNTAX	   Counter64
	MAX-ACCESS read-only
	STATUS	   current
	DESCRIPTION
		"Aggregated number of uplink multicast packet received for MCS08
		Device Allocation: AP"
	::= { wlanMCSPackets 57 }

ulWLanMCS09MulticastPackets OBJECT-TYPE
	SYNTAX	   Counter64
	MAX-ACCESS read-only
	STATUS	   current
	DESCRIPTION
		"Aggregated number of uplink multicast packet received for MCS09
		Device Allocation: AP"
	::= { wlanMCSPackets 58 }

ulWLanMCS10MulticastPackets OBJECT-TYPE
	SYNTAX	   Counter64
	MAX-ACCESS read-only
	STATUS	   current
	DESCRIPTION
		"Aggregated number of uplink multicast packet received for MCS10
		Device Allocation: AP"
	::= { wlanMCSPackets 59 }

ulWLanMCS11MulticastPackets OBJECT-TYPE
	SYNTAX	   Counter64
	MAX-ACCESS read-only
	STATUS	   current
	DESCRIPTION
		"Aggregated number of uplink multicast packet received for MCS11
		Device Allocation: AP"
	::= { wlanMCSPackets 60 }

ulWLanMCS12MulticastPackets OBJECT-TYPE
	SYNTAX	   Counter64
	MAX-ACCESS read-only
	STATUS	   current
	DESCRIPTION
		"Aggregated number of uplink multicast packet received for MCS12
		Device Allocation: AP"
	::= { wlanMCSPackets 61 }

ulWLanMCS13MulticastPackets OBJECT-TYPE
	SYNTAX	   Counter64
	MAX-ACCESS read-only
	STATUS	   current
	DESCRIPTION
		"Aggregated number of uplink multicast packet received for MCS13
		Device Allocation: AP"
	::= { wlanMCSPackets 62 }

ulWLanMCS14MulticastPackets OBJECT-TYPE
	SYNTAX	   Counter64
	MAX-ACCESS read-only
	STATUS	   current
	DESCRIPTION
		"Aggregated number of uplink multicast packet received for MCS14
		Device Allocation: AP"
	::= { wlanMCSPackets 63 }

ulWLanMCS15MulticastPackets OBJECT-TYPE
	SYNTAX	   Counter64
	MAX-ACCESS read-only
	STATUS	   current
	DESCRIPTION
		"Aggregated number of uplink multicast packet received for MCS15
		Device Allocation: AP"
	::= { wlanMCSPackets 64 }

syslogServerIPFirst	 OBJECT-TYPE
	SYNTAX	   IpAddress
	MAX-ACCESS read-write
	STATUS	   current
	DESCRIPTION
		"Syslog Server IP Address 1
		Device Allocation: AP, SM"
	::= { cambiumSystemLog 1 }

syslogServerIPSecond  OBJECT-TYPE
	SYNTAX	   IpAddress
	MAX-ACCESS read-write
	STATUS	   current
	DESCRIPTION
		"Syslog Server IP Address 2
		Device Allocation: AP, SM"
	::= { cambiumSystemLog 2 }

syslogServerIPThird	 OBJECT-TYPE
	SYNTAX	   IpAddress
	MAX-ACCESS read-write
	STATUS	   current
	DESCRIPTION
		"Syslog Server IP Address 3
		Device Allocation: AP, SM"
	::= { cambiumSystemLog 3 }

syslogServerIPFourth  OBJECT-TYPE
	SYNTAX	   IpAddress
	MAX-ACCESS read-write
	STATUS	   current
	DESCRIPTION
		"Syslog Server IP Address 4
		Device Allocation: AP, SM"
	::= { cambiumSystemLog 4 }

syslogServerLogToWeb  OBJECT-TYPE
	SYNTAX	   Integer32 (0|1)
	MAX-ACCESS read-write
	STATUS	   current
	DESCRIPTION
		"Enable Log to WEB Interface:
			0 - Disable,
			1 - Enable
		Device Allocation: AP, SM"
	DEFVAL	{ 0 }
	::= { cambiumSystemLog 5 }

syslogServerLogMask	 OBJECT-TYPE
	SYNTAX	   Integer32 (0..255)
	MAX-ACCESS read-write
	STATUS	   current
	DESCRIPTION
		"Log Level Mask:
			0   (0x00) - all messages,
			1   (0x01) - emerg,
			2   (0x02) - alert,
			4   (0x04) - crit,
			8   (0x08) - err,
			16  (0x10) - warning,
			32  (0x20) - notice,
			64  (0x40) - info,
			128 (0x80) - debug
		Device Allocation: AP, SM"
	DEFVAL	{ 0 }
	::= { cambiumSystemLog 6 }

syslogServerLogDA  OBJECT-TYPE
	SYNTAX     Integer32 (0|1)
	MAX-ACCESS read-write
	STATUS     current
	DESCRIPTION
		"Enable Device Agent logging to syslog:
			0 - Disabled
			1 - Enabled"
	::= { cambiumSystemLog 7 }

syslogServerLogCLISH  OBJECT-TYPE
	SYNTAX     Integer32 (0|1)
	MAX-ACCESS read-write
	STATUS     current
	DESCRIPTION
		"Enable clish logging to syslog:
			0 - Disabled
			1 - Enabled"
	DEFVAL	{ 1 }
	::= { cambiumSystemLog 8 }

syslogServerPortFirst	OBJECT-TYPE
	SYNTAX	   Integer32 (0..65535)
	MAX-ACCESS read-write
	STATUS	   current
	DESCRIPTION
		"Syslog Server IP port 1
			0 - will be replaced with the default port (514)
		Device Allocation: AP, SM"
	::= { cambiumSystemLog 11 }

syslogServerPortSecond	OBJECT-TYPE
	SYNTAX	   Integer32 (0..65535)
	MAX-ACCESS read-write
	STATUS	   current
	DESCRIPTION
		"Syslog Server IP port 2
				0 - will be replaced with the default port (514)
		Device Allocation: AP, SM"
	::= { cambiumSystemLog 12 }

syslogServerPortThird 	OBJECT-TYPE
	SYNTAX	   Integer32 (0..65535)
	MAX-ACCESS read-write
	STATUS	   current
	DESCRIPTION
		"Syslog Server IP port 3
				0 - will be replaced with the default port (514)
		Device Allocation: AP, SM"
	::= { cambiumSystemLog 13 }

syslogServerPortFourth 	OBJECT-TYPE
	SYNTAX	   Integer32 (0..65535)
	MAX-ACCESS read-write
	STATUS	   current
	DESCRIPTION
		"Syslog Server IP port 4
				0 - will be replaced with the default port (514)
		Device Allocation: AP, SM"
	::= { cambiumSystemLog 14 }

dhcpLanEnable  OBJECT-TYPE
	SYNTAX	   Integer32 (0|1)
	MAX-ACCESS read-write
	STATUS	   current
	DESCRIPTION
		"Local DHCP Server Enable:
			0 - Disable
			1 - Enable
		Device Allocation: SM"
	DEFVAL	{ 0 }
	::= { cambiumDHCP 1 }

dhcpLanStart  OBJECT-TYPE
	SYNTAX	   Integer32 (1..2147483647)
	MAX-ACCESS read-write
	STATUS	   current
	DESCRIPTION
		"Local DHCP Server IP Start Address
		Offset from the Network address.
		Device Allocation: SM"
	DEFVAL	{ 1 }
	::= { cambiumDHCP 2 }

dhcpLanLimit  OBJECT-TYPE
	SYNTAX	   Integer32 (1..2147483647)
	MAX-ACCESS read-write
	STATUS	   current
	DESCRIPTION
		"Local DHCP Server IP End Address
		Offset from the Network address.
		Device Allocation: SM"
	DEFVAL	{ 10 }
	::= { cambiumDHCP 3 }

dhcpLanLeasetime  OBJECT-TYPE
	SYNTAX	   Integer32 (0..24)
	MAX-ACCESS read-write
	STATUS	   current
	DESCRIPTION
		"Local DHCP Lease Setup in hours
		Valid Range: 1 hour - 24 hours
		Device Allocation: SM"
	DEFVAL	{ 24 }
	::= { cambiumDHCP 4 }

dhcpLanHostTable  OBJECT-TYPE
	SYNTAX SEQUENCE OF DhcpLanHostEntry
	MAX-ACCESS not-accessible
	STATUS	   current
	DESCRIPTION
		"Table for DHCP Hosts
		Device Allocation: SM"
	::= { cambiumDHCP 5 }

dhcpLanHostEntry  OBJECT-TYPE
	SYNTAX	DhcpLanHostEntry
	MAX-ACCESS not-accessible
	STATUS	   current
	DESCRIPTION
		"DHCP Hosts Table Entry
		Device Allocation: SM"
	INDEX	{ dhcpLanHostIndex }
	::= { dhcpLanHostTable 1 }

DhcpLanHostEntry ::= SEQUENCE {
	dhcpLanHostIndex
		Integer32,
	dhcpLanHostIP
		IpAddress,
	dhcpLanHostMAC
		DisplayString,
	dhcpLanHostName
		DisplayString
}

dhcpLanHostIndex OBJECT-TYPE
	SYNTAX	   Integer32 (0..8)
	MAX-ACCESS read-write
	STATUS	   current
	DESCRIPTION
		"DHCP host Table Index
		Table Entry is cleared if Index is set to zero
		Device Allocation: SM"
	::= { dhcpLanHostEntry 1 }

dhcpLanHostIP  OBJECT-TYPE
	SYNTAX	   IpAddress
	MAX-ACCESS read-write
	STATUS	   current
	DESCRIPTION
		"DHCP Lan Host IP
		'ignore' or the IP address to be used for DHCP host
		Device Allocation: SM"
	::= { dhcpLanHostEntry 2 }

dhcpLanHostMAC	OBJECT-TYPE
	SYNTAX	   DisplayString (SIZE(0|17))
	MAX-ACCESS read-write
	STATUS	   current
	DESCRIPTION
		"The hardware address of this host
		Device Allocation: SM"
	::= { dhcpLanHostEntry 3 }

dhcpLanHostName	 OBJECT-TYPE
	SYNTAX	   DisplayString (SIZE(0|1..128))
	MAX-ACCESS read-write
	STATUS	   current
	DESCRIPTION
		"Optional hostname to assign
		Device Allocation: SM"
	::= { dhcpLanHostEntry 4 }

dhcpOption82  OBJECT-TYPE
	SYNTAX	   Integer32 (0|1)
	MAX-ACCESS read-write
	STATUS	   current
	DESCRIPTION
		"DHCP Option82:
		 0 - Disable
		 1 - Enable
		Device Allocation: AP"
	DEFVAL	{ 0 }
	::= { cambiumDHCP 6 }

dhcpOption66  OBJECT-TYPE
	SYNTAX	   Integer32 (0|1)
	MAX-ACCESS read-write
	STATUS	   current
	DESCRIPTION
		"Device Configuration Management via DHCP Option 66:
		 0 - Disable
		 1 - Enable
		Device Allocation: AP, SM"
	DEFVAL	{ 1 }
	::= { cambiumDHCP 7 }

dhcpOption82CircuitIDType  OBJECT-TYPE
	SYNTAX	   Integer32 (0..4)
	MAX-ACCESS read-write
	STATUS	   current
	DESCRIPTION
		"DHCP Option 82 Circuit ID format:
		 0 - AP MAC(proprietary)
		 1 - AP MAC(ASCII)
		 2 - SSID
		 3 - AP hostname
		 4 - custom
		Device Allocation: AP"
	DEFVAL	{ 0 }
	::= { cambiumDHCP 8 }


dhcpOption82CircuitValue  OBJECT-TYPE
	SYNTAX	   DisplayString (SIZE(0|1..31))
	MAX-ACCESS read-write
	STATUS	   current
	DESCRIPTION
		"DHCP Option 82 Circuit ID value defined by user
		Device Allocation: AP"
	::= { cambiumDHCP 9 }

dhcpOption82RemoteIDType  OBJECT-TYPE
	SYNTAX	   Integer32 (0..4)
	MAX-ACCESS read-write
	STATUS	   current
	DESCRIPTION
		"DHCP Option 82 Remote ID format:
		 0 - MAC(proprietary)
		 1 - MAC(ASCII)
		 2 - SSID
		 3 - AP hostname
		 4 - custom
		Device Allocation: AP"
	DEFVAL	{ 0 }
	::= { cambiumDHCP 10 }

dhcpOption82RemoteValue  OBJECT-TYPE
	SYNTAX	   DisplayString (SIZE(0|1..31))
	MAX-ACCESS read-write
	STATUS	   current
	DESCRIPTION
		"DHCP Option 82 Remote ID value defined by user
		Device Allocation: AP"
	::= { cambiumDHCP 11 }

cambiumSSHServerEnable	OBJECT-TYPE
	SYNTAX	   Integer32 (0|1)
	MAX-ACCESS read-write
	STATUS	   current
	DESCRIPTION
		"Cambium SSH Server:
			0 - Disable,
			1 - Enable
		Device Allocation: AP, SM"
	DEFVAL	{ 1 }
	::= { cambiumSSHServer 1 }

cambiumSSHServerPort	OBJECT-TYPE
	SYNTAX	   Integer32 (1..65535)
	MAX-ACCESS read-write
	STATUS	   current
	DESCRIPTION
		"Cambium SSH Server Port Number.
		Device Allocation: AP, SM"
	DEFVAL	{ 22 }
	::= { cambiumSSHServer 2 }

cambiumSSHServerDeprecatedAlgorithms	OBJECT-TYPE
	SYNTAX	   Integer32 (0|1)
	MAX-ACCESS read-write
	STATUS	   current
	DESCRIPTION
		"Cambium SSH Server: support deprecated algorithms
			0 - Disable
			1 - Enable
		Device Allocation: AP, SM"
	DEFVAL	{ 0 }
	::= { cambiumSSHServer 3 }

networkMode	 OBJECT-TYPE
	SYNTAX	   Integer32 (1|2|3)
	MAX-ACCESS read-write
	STATUS	   current
	DESCRIPTION
		"SM Network Mode:
			1 - NAT,
			2 - Bridge,
			3 - Router
		Device Allocation: SM"
	::= { network 1 }

networkSTP OBJECT-TYPE
	SYNTAX	   Integer32 (0|1)
	MAX-ACCESS read-write
	STATUS	   current
	DESCRIPTION
		"Spanning Tree Protocol:
			0 - Disable STP (Default mode)
			1 - Enable STP
		Device Allocation: AP, SM"
	DEFVAL	{ 0 }
	::= { network 6 }

networkLanIPAddressMode	 OBJECT-TYPE
	SYNTAX	   Integer32 (1|2)
	MAX-ACCESS read-write
	STATUS	   current
	DESCRIPTION
		"SM NAT LAN IP Address Mode
			1 - Static,
			2 - DHCP
		Device Allocation: AP, SM"
	DEFVAL	{ 1 }
	::= { networkLan 1 }

networkLanIPAddr  OBJECT-TYPE
	SYNTAX	   IpAddress
	MAX-ACCESS read-write
	STATUS	   current
	DESCRIPTION
		"SM NAT LAN IP Address
		Device Allocation: SM"
	::= { networkLan 2 }

networkLanNetmask  OBJECT-TYPE
	SYNTAX	   IpAddress
	MAX-ACCESS read-write
	STATUS	   current
	DESCRIPTION
		"SM NAT LAN IP Subnet Mask
		Device Allocation: SM"
	::= { networkLan 3 }

networkLanGatewayIP	 OBJECT-TYPE
	SYNTAX	   IpAddress
	MAX-ACCESS read-write
	STATUS	   current
	DESCRIPTION
		"SM NAT LAN Gateway IP Address
		Device Allocation: SM"
	::= { networkLan 4 }

networkLanDNSIPAddr	 OBJECT-TYPE
	SYNTAX	   IpAddress
	MAX-ACCESS read-write
	STATUS	   obsolete
	DESCRIPTION
		"SM NAT LAN DNS Server IP Address
		Device Allocation: SM"
	::= { networkLan 5 }

networkLanMTU  OBJECT-TYPE
	SYNTAX	   Integer32 (0|576..3508)
	MAX-ACCESS read-write
	STATUS	   current
	DESCRIPTION
		"SM NAT LAN MTU size
		For 802.11n and Force devices maximum value is 1700 and default is 1500
		Device Allocation: SM"
	::= { networkLan 6 }

networkLanDNSIPAddrPrimary	OBJECT-TYPE
	SYNTAX	   IpAddress
	MAX-ACCESS read-write
	STATUS	   current
	DESCRIPTION
		"SM NAT LAN DNS Server IP Address
		Device Allocation: SM
		Primary Server IP"
	::= { networkLan 7 }

networkLanDNSIPAddrSecondary  OBJECT-TYPE
	SYNTAX	   IpAddress
	MAX-ACCESS read-write
	STATUS	   current
	DESCRIPTION
		"SM NAT LAN DNS Server IP Address
		Device Allocation: SM
		Secondary Server IP"
	::= { networkLan 8 }

networkLanAutoNegotiation  OBJECT-TYPE
	SYNTAX	   Integer32 (0|1)
	MAX-ACCESS read-write
	STATUS	   current
	DESCRIPTION
		"Lan Autonegotiation
			0 - Disable,
			1 - Enable
		Device Allocation: AP, SM"
	DEFVAL	{ 1 }
	::= { networkLan 9 }

networkLanSpeed	 OBJECT-TYPE
	SYNTAX	   Integer32 (10|100|1000|10000)
	MAX-ACCESS read-write
	STATUS	   current
	DESCRIPTION
		"LAN Speed
			10	 - 10 Mb/s,
			100	 - 100 Mb/s,
			1000 - 1000 Mb/s
		Device Allocation: AP, SM"
	DEFVAL	{ 100 }
	::= { networkLan 10 }

networkLanDuplex  OBJECT-TYPE
	SYNTAX	   Integer32 (0|1)
	MAX-ACCESS read-write
	STATUS	   current
	DESCRIPTION
		"LAN Duplex Mode
			0 - Half,
			1 - Full
		Device Allocation: AP, SM"
	DEFVAL	{ 1 }
	::= { networkLan 11 }

networkBroadcastStormEnabled  OBJECT-TYPE
	SYNTAX	   Integer32 (0|1)
	MAX-ACCESS read-write
	STATUS	   current
	DESCRIPTION
		"Broadcast Storm Control
			0 - Disabled,
			1 - Enabled
		Device Allocation: AP, SM"
	DEFVAL	{ 0 }
	::= { networkLan 12 }

networkBroadcastStormRate  OBJECT-TYPE
	SYNTAX	   Integer32 (100..16000)
	MAX-ACCESS read-write
	STATUS	   current
	DESCRIPTION
		"Broadcast Storm Control Rate
			in frames per second
		Device Allocation: AP, SM"
	::= { networkLan 13 }

networkLanSmartSpeedMode   OBJECT-TYPE
	SYNTAX	    Integer32 (0|1)
	MAX-ACCESS  read-write
	STATUS	    current
	DESCRIPTION
		"Auto-negotiation 'Smart Speed' feature.
		Enables speed regulation based on cabling conditions.
			0 - Disabled
			1 - Enabled
		Device Allocation: AP, SM"
	DEFVAL	{ 1 }
	::= { networkLan 14 }

networkLan2Enabled	OBJECT-TYPE
	SYNTAX	   Integer32 (0|1)
	MAX-ACCESS read-write
	STATUS	   current
	DESCRIPTION
		"AUX Lan Port Enabled
			0 - Disable,
			1 - Enable
		Device Allocation: AP, SM"
	DEFVAL	{ 1 }
	::= { networkLan 20 }

networkLan2AutoNegotiation	OBJECT-TYPE
	SYNTAX	   Integer32 (0|1)
	MAX-ACCESS read-write
	STATUS	   current
	DESCRIPTION
		"Lan Autonegotiation
			0 - Disable,
			1 - Enable
		Device Allocation: AP, SM"
	DEFVAL	{ 1 }
	::= { networkLan 21 }

networkLan2Speed  OBJECT-TYPE
	SYNTAX	   Integer32 (10|100|1000|10000)
	MAX-ACCESS read-write
	STATUS	   current
	DESCRIPTION
		"LAN Speed
			10	 - 10 Mb/s,
			100	 - 100 Mb/s,
			1000 - 1000 Mb/s
		Device Allocation: AP, SM"
	DEFVAL	{ 1000 }
	::= { networkLan 22 }

networkLan2Duplex  OBJECT-TYPE
	SYNTAX	   Integer32 (0|1)
	MAX-ACCESS read-write
	STATUS	   current
	DESCRIPTION
		"LAN Duplex Mode
			0 - Half,
			1 - Full
		Device Allocation: AP, SM"
	DEFVAL	{ 1 }
	::= { networkLan 23 }

networkLan2PoEEnabled  OBJECT-TYPE
	SYNTAX	   Integer32 (0|1)
	MAX-ACCESS read-write
	STATUS	   current
	DESCRIPTION
		"PoE Enabled
			0 - Disabled,
			1 - Enabled
		Device Allocation: SM"
	DEFVAL	{ 1 }
	::= { networkLan 24 }

networkLanEnabled  OBJECT-TYPE
	SYNTAX	   Integer32 (0|1)
	MAX-ACCESS read-write
	STATUS	   current
	DESCRIPTION
		"Lan Port Enabled
			0 - Disable,
			1 - Enable
		Device Allocation: SM"
	DEFVAL	{ 1 }
	::= { networkLan 25 }

networkLan2MTU  OBJECT-TYPE
	SYNTAX     Integer32 (0|576..3508)
	MAX-ACCESS read-write
	STATUS     current
	DESCRIPTION
		"SM NAT LAN2 MTU size
		For 802.11ac devices only
		Device Allocation: SM"
	::= { networkLan 26 }

networkLanAdvertise  OBJECT-TYPE
	SYNTAX		Integer32
	MAX-ACCESS	read-write
	STATUS		current
	DESCRIPTION
		"Lan Port speed and duplex advertised by autonegotiation.
		Value is a decimal number which represents a bitmask constructed
		using following values:
			0x001	10baseT Half
			0x002	10baseT Full
			0x004	100baseT Half
			0x008	100baseT Full
			0x010	1000baseT Half       (not supported by IEEE standards)
			0x020	1000baseT Full
		Device Allocation: AP, SM"
	DEFVAL	{ 47 }
	::= { networkLan 27 }

networkLanIPv6Addr  OBJECT-TYPE
	SYNTAX     Ipv6Address
	MAX-ACCESS read-write
	STATUS     current
	DESCRIPTION
		"SM NAT LAN IPv6 Address
		Device Allocation: SM"
	::= { networkLan 31 }

networkLanGatewayIPv6 OBJECT-TYPE
	SYNTAX     Ipv6Address
	MAX-ACCESS read-write
	STATUS     current
	DESCRIPTION
		"SM NAT LAN Gateway IPv6 Address
		Device Allocation: SM"
	::= { networkLan 32 }

networkLanIPv6AddressType OBJECT-TYPE
	SYNTAX     Integer32 (0..2)
	MAX-ACCESS read-write
	STATUS     current
	DESCRIPTION
		"SM NAT LAN IPv6 Address Type
			0 - Local,
			1 - Static,
			2 - Prefix Delegation
		Device Allocation: SM"
	::= { networkLan 33 }

networkLanIPv6PrefixLength OBJECT-TYPE
	SYNTAX     Integer32 (1..128)
	MAX-ACCESS read-write
	STATUS     current
	DESCRIPTION
		"SM NAT LAN IPv6 Prefix Length
		Device Allocation: SM"
	::= { networkLan 34 }

networkLanIPv6DHCPServer OBJECT-TYPE
	SYNTAX     Integer32 (0..2)
	MAX-ACCESS read-write
	STATUS     current
	DESCRIPTION
		"SM NAT LAN IPv6 DHCPv6 Server Type
			0 - Disabled,
			1 - Stateless,
			2 - Stateful
		Device Allocation: SM"
	::= { networkLan 35 }

lanSwitchPortTable OBJECT-TYPE
	SYNTAX SEQUENCE OF LanSwitchPortEntry
	MAX-ACCESS not-accessible
	STATUS     current
	DESCRIPTION
		"Lan Switch Port Table"
	::= { lanSwitch 10 }

lanSwitchPortEntry OBJECT-TYPE
	SYNTAX     LanSwitchPortEntry
	MAX-ACCESS not-accessible
	STATUS     current
	DESCRIPTION
		"Lan Switch Port Entry
		Device Allocation: AP, SM"
	INDEX   { lanSwitchPortNum }
	::= { lanSwitchPortTable 1 }

LanSwitchPortEntry ::= SEQUENCE {
	lanSwitchPortNum
		Integer32,
	lanSwitchPortEnable
		Integer32,
	lanSwitchPortAutoneg
		Integer32,
	lanSwitchPortSpeed
		Integer32,
	lanSwitchPortDuplex
		Integer32,
	lanSwitchPortPoEMode
		Integer32
}

lanSwitchPortNum OBJECT-TYPE
	SYNTAX     Integer32 (1..32)
	MAX-ACCESS read-only
	STATUS     current
	DESCRIPTION
		"Device port number.
		Device Allocation: AP, SM"
	::= { lanSwitchPortEntry 1 }

lanSwitchPortEnable OBJECT-TYPE
	SYNTAX     Integer32 (0|1)
	MAX-ACCESS read-write
	STATUS     current
	DESCRIPTION
		"Switch Port Enable
		0 - Disable,
		1 - Enable
		Device Allocation: AP, SM"
	::= { lanSwitchPortEntry 2 }

lanSwitchPortAutoneg OBJECT-TYPE
	SYNTAX     Integer32 (0|1)
	MAX-ACCESS read-write
	STATUS     current
	DESCRIPTION
		"Switch Port Autonegotiation
		0 - Disable,
		1 - Enable
		Device Allocation: AP, SM"
	::= { lanSwitchPortEntry 3 }

lanSwitchPortSpeed OBJECT-TYPE
	SYNTAX     Integer32 (10|100|1000)
	MAX-ACCESS read-write
	STATUS     current
	DESCRIPTION
		"Switch Port Speed
		10   - 10 Mb/s,
		100  - 100 Mb/s,
		1000 - 1000 Mb/s
		Device Allocation: AP, SM"
	::= { lanSwitchPortEntry 4 }

lanSwitchPortDuplex OBJECT-TYPE
	SYNTAX     Integer32 (0|1)
	MAX-ACCESS read-write
	STATUS     current
	DESCRIPTION
		"Switch Port Duplex Mode
		0 - Half,
		1 - Full
		Device Allocation: AP, SM"
	::= { lanSwitchPortEntry 5 }

lanSwitchPortPoEMode OBJECT-TYPE
	SYNTAX     Integer32 (0|1|2|3)
	MAX-ACCESS read-write
	STATUS     current
	DESCRIPTION
		"Switch Port PoE Enable
		0 - Off,
		1 - Passive 56V,
		2 - Active 56V,
		3 - Passive 24V
		Device Allocation: AP, SM"
	::= { lanSwitchPortEntry 6 }

networkWanIPAddressMode	 OBJECT-TYPE
	SYNTAX	   Integer32 (1|2)
	MAX-ACCESS read-write
	STATUS	   current
	DESCRIPTION
		"SM NAT WAN IP Address Mode
			1 - Static,
			2 - DHCP
		Device Allocation: SM"
	DEFVAL	{ 1 }
	::= { networkWan 1 }

networkWanIPAddr  OBJECT-TYPE
	SYNTAX	   IpAddress
	MAX-ACCESS read-write
	STATUS	   current
	DESCRIPTION
		"SM NAT WAN IP Address
		Device Allocation: SM"
	::= { networkWan 2 }

networkWanNetmask  OBJECT-TYPE
	SYNTAX	   IpAddress
	MAX-ACCESS read-write
	STATUS	   current
	DESCRIPTION
		"SM NAT WAN IP Subnet Mask
		Device Allocation: SM"
	::= { networkWan 3 }

networkWanGatewayIP	 OBJECT-TYPE
	SYNTAX	   IpAddress
	MAX-ACCESS read-write
	STATUS	   current
	DESCRIPTION
		"SM NAT WAN Gateway IP Address
		Device Allocation: SM"
	::= { networkWan 4 }

networkWanDNSIPAddr	 OBJECT-TYPE
	SYNTAX	   IpAddress
	MAX-ACCESS read-write
	STATUS	   obsolete
	DESCRIPTION
		"SM NAT WAN DNS Server IP Address
		Device Allocation: SM"
	::= { networkWan 5 }

networkWanMTU  OBJECT-TYPE
	SYNTAX	   Integer32 (0|576..3508)
	MAX-ACCESS read-write
	STATUS	   current
	DESCRIPTION
		"SM NAT WAN MTU size
		For 802.11n and Force devices maximum value is 1700
		Device Allocation: SM"
	DEFVAL	{ 1500 }
	::= { networkWan 6 }

networkWanDNSIPAddrPrimary	OBJECT-TYPE
	SYNTAX	   IpAddress
	MAX-ACCESS read-write
	STATUS	   current
	DESCRIPTION
		"SM NAT WAN DNS Server IP Address
		Device Allocation: SM
		Primary Server IP"
	::= { networkWan 7 }

networkWanDNSIPAddrSecondary  OBJECT-TYPE
	SYNTAX	   IpAddress
	MAX-ACCESS read-write
	STATUS	   current
	DESCRIPTION
		"SM NAT WAN DNS Server IP Address
		Device Allocation: SM
		Secondary Server IP"
	::= { networkWan 8 }

networkWanPPPoE	 OBJECT-TYPE
	SYNTAX	   Integer32 (0|1)
	MAX-ACCESS read-write
	STATUS	   current
	DESCRIPTION
		"SM only.Enable or Disable PPPoE
		mode. 1 is enable 0 is disable"
	DEFVAL	{ 0 }
	::= { networkWan 9 }

networkWanPPPoEUsername	 OBJECT-TYPE
	SYNTAX	   DisplayString (SIZE(0..128))
	MAX-ACCESS read-write
	STATUS	   current
	DESCRIPTION
		"SM only. Username to authenticate with
		PPPoE Server.
		Only private community can read this attribute."
	::= { networkWan 10 }

networkWanPPPoEPassword	 OBJECT-TYPE
	SYNTAX	   OCTET STRING (SIZE(0..128))
	MAX-ACCESS read-write
	STATUS	   current
	DESCRIPTION
		"SM only. Password to authenticate with
		PPPoE Server.
		Only private community can read this attribute."
	::= { networkWan 11 }

networkWanPPPoEAC  OBJECT-TYPE
	SYNTAX	   DisplayString (SIZE(0..128))
	MAX-ACCESS read-write
	STATUS	   current
	DESCRIPTION
		"SM only.PPPoE Access Concentrator Name"
	::= { networkWan 12 }

networkWanPPPoEService	OBJECT-TYPE
	SYNTAX	   DisplayString (SIZE(0..128))
	MAX-ACCESS read-write
	STATUS	   current
	DESCRIPTION
		"SM only.PPPoE Service Name"
	::= { networkWan 13 }

networkWanPPPoEAuth	 OBJECT-TYPE
	SYNTAX	   Integer32 (0|1|2)
	MAX-ACCESS read-write
	STATUS	   current
	DESCRIPTION
		"SM only.This indicates type of authentication
		with PPPoE Server. Options are
		0 - All
		1 - PAP
		2 - CHAP"
	DEFVAL	{ 0 }
	::= { networkWan 14 }

networkWanPPPoEMTU	OBJECT-TYPE
	SYNTAX	   Integer32 (0|576..1492)
	MAX-ACCESS read-write
	STATUS	   current
	DESCRIPTION
		"SM only.MTU size to be used for PPPoE
		connection"
	DEFVAL	{ 1492 }
	::= { networkWan 15 }

networkWanPPPoEKeepAlive OBJECT-TYPE
	SYNTAX	   Integer32 (0|5..180)
	MAX-ACCESS read-write
	STATUS	   current
	DESCRIPTION
		"SM only.Time in seconds for the keep Alive
		messages from PPPoE client to PPPoE
		Server"
	DEFVAL	{ 10 }
	::= { networkWan 16 }

networkWanPPPoEMSSClamping OBJECT-TYPE
	SYNTAX	   Integer32 (0|1)
	MAX-ACCESS read-write
	STATUS	   current
	DESCRIPTION
		"SM only.Enable or disable MSS Clamping
		0 - Disable
		1 - Enable"
	DEFVAL	{ 0 }
	::= { networkWan 17 }

networkWanPPPoEAttempts OBJECT-TYPE
	SYNTAX	   Integer32 (0|1..15)
	MAX-ACCESS read-write
	STATUS	   current
	DESCRIPTION
		"SM only.Maximum number of echo attempts
		before considering the link to be dead"
	DEFVAL	{ 5 }
	::= { networkWan 18 }

networkPPPoEIAEnable OBJECT-TYPE
	SYNTAX     Integer32 (0|1)
	MAX-ACCESS read-write
	STATUS     current
	DESCRIPTION
		"PPPoE Intermediate Agent
		0 - Disable
		1 - Enable
		Device Allocation: AP"
	DEFVAL  { 0 }
	::= { networkPPPoE 1 }

networkPPPoEIATable   OBJECT-TYPE
	SYNTAX SEQUENCE OF NetworkPPPoEIAEntry
	MAX-ACCESS not-accessible
	STATUS     current
	DESCRIPTION
		"PPPoE IA Table"
	::= { networkPPPoE 2 }

networkPPPoEIAEntry OBJECT-TYPE
	SYNTAX     NetworkPPPoEIAEntry
	MAX-ACCESS not-accessible
	STATUS     current
	DESCRIPTION
		"PPPoE IA Table Entry
		Device Allocation: AP"
	INDEX   { networkPPPoEIAIndex }
	::= { networkPPPoEIATable 1 }

NetworkPPPoEIAEntry ::= SEQUENCE {
	networkPPPoEIAIndex
	Integer32,
	networkPPPoEIAUID
	Integer32,
	networkPPPoEIASMMAC
	DisplayString,
	networkPPPoEIAPhoneNumber
	DisplayString,
	networkPPPoEIATerminal
	DisplayString,
	networkPPPoEIAFrame
	DisplayString,
	networkPPPoEIASlot
	DisplayString,
	networkPPPoEIAPort
	DisplayString,
	networkPPPoEIAVlanId
	Integer32
}

networkPPPoEIAIndex OBJECT-TYPE
	SYNTAX     Integer32 (0..127)
	MAX-ACCESS read-write
	STATUS     current
	DESCRIPTION
		"PPPoE IA Table Index
		Table Entry is cleared if Index is set to zero
		Device Allocation: AP"
	::= { networkPPPoEIAEntry 1 }

networkPPPoEIAUID OBJECT-TYPE
	SYNTAX     Integer32 (1..128)
	MAX-ACCESS read-write
	STATUS     current
	DESCRIPTION
		"PPPoE IA UID
		Device Allocation: AP"
	::= { networkPPPoEIAEntry 2 }

networkPPPoEIASMMAC OBJECT-TYPE
	SYNTAX     DisplayString (SIZE(0|11..17))
	MAX-ACCESS read-write
	STATUS     current
	DESCRIPTION
		"PPPoE IA Registered SM MAC Address
		Device Allocation: AP"
	::= { networkPPPoEIAEntry 3 }

networkPPPoEIAPhoneNumber OBJECT-TYPE
	SYNTAX     DisplayString (SIZE(0..63))
	MAX-ACCESS read-write
	STATUS     current
	DESCRIPTION
		"PPPoE IA Remote ID
		Device Allocation: AP"
	::= { networkPPPoEIAEntry 4 }

networkPPPoEIATerminal OBJECT-TYPE
	SYNTAX     DisplayString (SIZE(0..3))
	MAX-ACCESS read-write
	STATUS     current
	DESCRIPTION
		"PPPoE IA Terminal ID
		Device Allocation: AP"
	::= { networkPPPoEIAEntry 5 }

networkPPPoEIAFrame OBJECT-TYPE
	SYNTAX     DisplayString (SIZE(0..1))
	MAX-ACCESS read-write
	STATUS     current
	DESCRIPTION
		"PPPoE IA Frame ID
		Device Allocation: AP"
	::= { networkPPPoEIAEntry 6 }

networkPPPoEIASlot OBJECT-TYPE
	SYNTAX     DisplayString (SIZE(0..2))
	MAX-ACCESS read-write
	STATUS     current
	DESCRIPTION
		"PPPoE IA Slot
		Device Allocation: AP"
	::= { networkPPPoEIAEntry 7 }

networkPPPoEIAPort OBJECT-TYPE
	SYNTAX     DisplayString (SIZE(0..1))
	MAX-ACCESS read-write
	STATUS     current
	DESCRIPTION
		"PPPoE IA Port number
		Device Allocation: AP"
	::= { networkPPPoEIAEntry 8 }

networkPPPoEIAVlanId OBJECT-TYPE
	SYNTAX     Integer32 (1..4095)
	MAX-ACCESS read-write
	STATUS     current
	DESCRIPTION
		"PPPoE IA VLAN ID
		Device Allocation: AP"
	::= { networkPPPoEIAEntry 9 }

networkWanIPv6AddressMode  OBJECT-TYPE
	SYNTAX     Integer32 (0..3)
	MAX-ACCESS read-write
	STATUS     current
	DESCRIPTION
		"SM NAT WAN IPv6 Address Mode
			0 - Local,
			1 - Static,
			2 - DHCPv6,
			3 - SLAAC
		Device Allocation: SM"
	DEFVAL  { 1 }
	::= { networkWan 30 }

networkWanIPv6Addr  OBJECT-TYPE
	SYNTAX     Ipv6Address
	MAX-ACCESS read-write
	STATUS     current
	DESCRIPTION
		"SM NAT WAN IPv6 Address
		Device Allocation: SM"
	::= { networkWan 31 }

networkWanGatewayIPv6  OBJECT-TYPE
	SYNTAX     Ipv6Address
	MAX-ACCESS read-write
	STATUS     current
	DESCRIPTION
		"SM NAT WAN IPv6 Gateway Address
		Device Allocation: SM"
	::= { networkWan 32 }

networkWanIPv6LocalInterfaceId OBJECT-TYPE
	SYNTAX	Ipv6Address
	MAX-ACCESS	read-write
	STATUS	current
	DESCRIPTION
		"SM NAT WAN IPv6 Local Interface Identifier
		Set the local 64-bit interface identifier.
		The identifier must be specified in standard ASCII notation of IPv6 addresses
		(for example: ::dead:beef).
		Device Allocation: SM"
	::= { networkWan 33 }

networkBridgeIPAddressMode	OBJECT-TYPE
	SYNTAX	   Integer32 (1|2)
	MAX-ACCESS read-write
	STATUS	   current
	DESCRIPTION
		"Device Bridge IP Address Mode
			1 - Static,
			2 - DHCP
		Device Allocation: AP, SM"
	DEFVAL	{ 1 }
	::= { networkBridge 1 }

networkBridgeIPAddr	 OBJECT-TYPE
	SYNTAX	   IpAddress
	MAX-ACCESS read-write
	STATUS	   current
	DESCRIPTION
		"Device Bridge IP Address
		Device Allocation: AP, SM"
	::= { networkBridge 2 }

networkBridgeNetmask  OBJECT-TYPE
	SYNTAX	   IpAddress
	MAX-ACCESS read-write
	STATUS	   current
	DESCRIPTION
		"Device Bridge IP Subnet Mask
		Device Allocation: AP, SM"
	::= { networkBridge 3 }

networkBridgeGatewayIP	OBJECT-TYPE
	SYNTAX	   IpAddress
	MAX-ACCESS read-write
	STATUS	   current
	DESCRIPTION
		"Device Bridge Gateway IP Address
		Device Allocation: AP, SM"
	::= { networkBridge 4 }

networkBridgeDNSIPAddr	OBJECT-TYPE
	SYNTAX	   IpAddress
	MAX-ACCESS read-write
	STATUS	   obsolete
	DESCRIPTION
		"Device Bridge DNS Server IP Address
		Device Allocation: AP, SM"
	::= { networkBridge 5 }

networkBridgeMTU  OBJECT-TYPE
	SYNTAX	   Integer32 (576..3508)
	MAX-ACCESS read-write
	STATUS	   current
	DESCRIPTION
		"Device Bridge MTU size
		For 802.11n and Force devices maximum value is 1700 and default is 1500
		Device Allocation: AP, SM"
	::= { networkBridge 6 }

networkBridgeDNSIPAddrPrimary  OBJECT-TYPE
	SYNTAX	   IpAddress
	MAX-ACCESS read-write
	STATUS	   current
	DESCRIPTION
		"Device Bridge DNS Server IP Address
		Device Allocation: AP, SM
		Primary Server IP"
	::= { networkBridge 7 }

networkBridgeDNSIPAddrSecondary	 OBJECT-TYPE
	SYNTAX	   IpAddress
	MAX-ACCESS read-write
	STATUS	   current
	DESCRIPTION
		"Device Bridge DNS Server IP Address
		Device Allocation: AP, SM
		Secondary Server IP"
	::= { networkBridge 8 }
networkBridgeIPv6AddressMode  OBJECT-TYPE
	SYNTAX     Integer32 (0..3)
	MAX-ACCESS read-write
	STATUS     current
	DESCRIPTION
		"Device Bridge IPv6 Address Mode
		0 - Local,
		1 - Static,
		2 - DHCPv6,
		3 - SLAAC
		Device Allocation: AP, SM"
	DEFVAL  { 1 }
	::= { networkBridge 30 }

networkBridgeIPv6Addr  OBJECT-TYPE
	SYNTAX     Ipv6Address
	MAX-ACCESS read-write
	STATUS     current
	DESCRIPTION
		"Device Bridge IPv6 Address
		Device Allocation: AP, SM"
	::= { networkBridge 31 }

networkBridgeGatewayIPv6  OBJECT-TYPE
	SYNTAX     Ipv6Address
	MAX-ACCESS read-write
	STATUS     current
	DESCRIPTION
		"Device Bridge IPv6 Gateway Address
		Device Allocation: AP, SM"
	::= { networkBridge 32 }

networkPortSecurity OBJECT-TYPE
	SYNTAX	   Integer32 (0|1)
	MAX-ACCESS read-write
	STATUS	   current
	DESCRIPTION
		"LAN Port Security switch:
			0 - Disable
			1 - Enable
		Device Allocation: SM"
	DEFVAL	{ 0 }
	::= { network 8 }

networkPortSecurityMax OBJECT-TYPE
	SYNTAX	   Integer32 (0..2047)
	MAX-ACCESS read-write
	STATUS	   current
	DESCRIPTION
		"Number of secure MAC addresses:
		1-2047 - Fixed Learned MAC limit
		Device Allocation: SM"
	DEFVAL	{ 5 }
	::= { network 9 }

networkPortSecurityAgingTime OBJECT-TYPE
	SYNTAX	   Integer32 (0..1440)
	MAX-ACCESS read-write
	STATUS	   current
	DESCRIPTION
		"Security MAC address aging time:
		This prameter indicates on how long to store learned MAC address in the cache in seconds,
		0 - do not delete MAC address from the buffer,
		Default - is 300 seconds.
		Device Allocation: AP, SM"
	DEFVAL	{ 300 }
	::= { network 10 }

mcastGroupLimit OBJECT-TYPE
	SYNTAX	   Integer32 (0|1..5)
	MAX-ACCESS read-write
	STATUS	   current
	DESCRIPTION
		"Multicast Group Limit:
		Default - 3 Multicast Groups for SM, unlimited for AP.
		Device Allocation: SM"
	DEFVAL	{ 3 }
	::= { network 17 }

mgmtIFEnable OBJECT-TYPE
	SYNTAX	   Integer32 (0|1)
	MAX-ACCESS read-write
	STATUS	   current
	DESCRIPTION
		"Separate Management Interface Enabled:
		0 - Disabled,
		1 - Enabled
		Device Allocation: SM"
	DEFVAL	{ 0 }
	::= { mgmtIF 1 }

mgmtIFVLAN OBJECT-TYPE
	SYNTAX	   Integer32 (0|1)
	MAX-ACCESS read-write
	STATUS	   current
	DESCRIPTION
		"Separate Management Interface VLAN Enabled:
		0 - Disabled,
		1 - Enabled
		Device Allocation: SM"
	DEFVAL	{ 0 }
	::= { mgmtIF 2 }

mgmtIFVID OBJECT-TYPE
	SYNTAX	   Integer32 (1..4094)
	MAX-ACCESS read-write
	STATUS	   current
	DESCRIPTION
		"Separate Management Interface VLAN
		Device Allocation: SM"
	::= { mgmtIF 3 }

mgmtIFVP OBJECT-TYPE
	SYNTAX	   Integer32 (0..7)
	MAX-ACCESS read-write
	STATUS	   current
	DESCRIPTION
		"Separate Management Interface VP
		Device Allocation: SM"
	::= { mgmtIF 4 }

mgmtIFIPAddressMode OBJECT-TYPE
	SYNTAX	   Integer32 (1|2)
	MAX-ACCESS read-write
	STATUS	   current
	DESCRIPTION
		"Separate Management IP Address Mode
		1 - Static,
		2 - DHCP
		Device Allocation: SM"
	::= { mgmtIF 5 }

mgmtIFIPAddr OBJECT-TYPE
	SYNTAX	   IpAddress
	MAX-ACCESS read-write
	STATUS	   current
	DESCRIPTION
		"Separate Management IP Address
		Device Allocation: SM"
	::= { mgmtIF 6 }

mgmtIFNetmask OBJECT-TYPE
	SYNTAX	   IpAddress
	MAX-ACCESS read-write
	STATUS	   current
	DESCRIPTION
		"Separate Management IP Subnet Mask
		Device Allocation: SM"
	::= { mgmtIF 7 }

mgmtIFGateway OBJECT-TYPE
	SYNTAX	   IpAddress
	MAX-ACCESS read-write
	STATUS	   current
	DESCRIPTION
		"Separate Management IP Gateway
		Device Allocation: SM"
	::= { mgmtIF 8 }
mgmtIFIPv6AddressMode OBJECT-TYPE
	SYNTAX     Integer32 (0..3)
	MAX-ACCESS read-write
	STATUS     current
	DESCRIPTION
		"Separate Management IPv6 Address Mode
			0 - Local,
			1 - Static,
			2 - DHCPv6,
			3 - SLAAC
		Device Allocation: SM"
	::= { mgmtIF 30 }

mgmtIFIPv6Addr OBJECT-TYPE
	SYNTAX     Ipv6Address
	MAX-ACCESS read-write
	STATUS     current
	DESCRIPTION
		"Separate Management IPv6 Address
		Device Allocation: SM"
	::= { mgmtIF 31 }

mgmtIFIPv6Gateway  OBJECT-TYPE
	SYNTAX     Ipv6Address
	MAX-ACCESS read-write
	STATUS     current
	DESCRIPTION
		"Separate Management IPv6 Gateway Address
		Device Allocation: SM"
	::= { mgmtIF 32 }

cambiumIPAliasCnfTable	 OBJECT-TYPE
	SYNTAX SEQUENCE OF CambiumIPAliasCnfEntry
	MAX-ACCESS not-accessible
	STATUS	   current
	DESCRIPTION
		"Static Network Table"
	::= { networkAliases 1 }

cambiumIPAliasCnfEntry OBJECT-TYPE
	SYNTAX	   CambiumIPAliasCnfEntry
	MAX-ACCESS not-accessible
	STATUS	   current
	DESCRIPTION
		"Static Network Table Entry
		Device Allocation: SM"
	INDEX	{ cambiumIPAliasesIndex }
	::= { cambiumIPAliasCnfTable 1 }

CambiumIPAliasCnfEntry ::= SEQUENCE {
	cambiumIPAliasesIndex
		Integer32,
	cambiumIPAliasesIpAddr
		IpAddress,
	cambiumIPAliasesNetmask
		IpAddress,
	cambiumIPAliasesInfo
		DisplayString,
	cambiumIPAliasesIface
		Integer32
}

cambiumIPAliasesIndex OBJECT-TYPE
	SYNTAX	   Integer32 (0..16)
	MAX-ACCESS read-write
	STATUS	   current
	DESCRIPTION
		"IP Alias Table Index
		Table Entry is cleared if Index is set to zero
		Device Allocation: AP, SM"
	::= { cambiumIPAliasCnfEntry 1 }

cambiumIPAliasesIpAddr	OBJECT-TYPE
	SYNTAX	   IpAddress
	MAX-ACCESS read-write
	STATUS	   current
	DESCRIPTION
		"Network IP Alliases address"
	::= { cambiumIPAliasCnfEntry 2 }

cambiumIPAliasesNetmask OBJECT-TYPE
	SYNTAX		IpAddress
	MAX-ACCESS	read-write
	STATUS		current
	DESCRIPTION
		"Network Dest IP Netmask"
	::= { cambiumIPAliasCnfEntry 3 }

cambiumIPAliasesInfo  OBJECT-TYPE
	SYNTAX	   DisplayString (SIZE(0..128))
	MAX-ACCESS read-write
	STATUS	   current
	DESCRIPTION
		"Network Info message"
	::= { cambiumIPAliasCnfEntry 4 }

cambiumIPAliasesIface  OBJECT-TYPE
	SYNTAX	   Integer32 (1|2)
	MAX-ACCESS read-write
	STATUS	   current
	DESCRIPTION
		"Alias Parent Interface
			1 - LAN,
			2 - WAN
		Device Allocation: AP, SM"
	::= { cambiumIPAliasCnfEntry 5 }

cambiumIPAliasesEnable	OBJECT-TYPE
	SYNTAX	   Integer32 (0|1)
	MAX-ACCESS read-write
	STATUS	   current
	DESCRIPTION
		"Enable/Disable IP Aliases in Router mode
		Device Allocation: SM"
	::= { networkAliases 2 }

networkLanDefaultIP OBJECT-TYPE
	SYNTAX	   IpAddress
	MAX-ACCESS read-write
	STATUS	   current
	DESCRIPTION
		"Default Network IP
		Device Allocation: SM"
	::= { network 25 }

networkRelaydEnable OBJECT-TYPE
	SYNTAX	   Integer32 (0|1)
	MAX-ACCESS read-write
	STATUS	   current
	DESCRIPTION
		"Relay for forwarding DHCP packets:
			0 - Disable
			1 - Enable
		Device Allocation: AP,SM"
	DEFVAL	{ 0 }
	::= { network 26 }

networkUPNP OBJECT-TYPE
	SYNTAX     Integer32 (0|1)
	MAX-ACCESS read-write
	STATUS     current
	DESCRIPTION
		"Enable UPnP on SM in NAT mode
		0 - Disable,
		1 - Enable
		Device Allocation: SM"
	::= { upnpd 1 }

networkNATPMP OBJECT-TYPE
	SYNTAX     Integer32 (0|1)
	MAX-ACCESS read-write
	STATUS     current
	DESCRIPTION
		"Enable NAT-PMP on SM in NAT mode
		0 - Disable,
		1 - Enable
		Device Allocation: SM"
	::= { upnpd 2 }

networkLLDP OBJECT-TYPE
	SYNTAX     Integer32 (0|1)
	MAX-ACCESS read-write
	STATUS     current
	DESCRIPTION
		"Enable LLDP
		0 - Disable,
		1 - Enable
		Device Allocation: AP,SM"
	::= { lldpd 1 }

networkLLDPMode OBJECT-TYPE
	SYNTAX     Integer32 (1|2)
	MAX-ACCESS read-write
	STATUS     current
	DESCRIPTION
		"LLDP mode
			1 - receive and transmit LLDPDU
			2 - only receive LLDPDU
		Device Allocation: AP,SM"
	::= { lldpd 2 }

networkMACTELNET OBJECT-TYPE
	SYNTAX     Integer32 (0|1)
	MAX-ACCESS read-write
	STATUS     current
	DESCRIPTION
		"Enable MAC-Telnet Service
		 0 - Disable,
		 1 - Enable
		 Device Allocation: AP,SM"
	DEFVAL { 0 }
	::= { mactelnet 1 }

networkMACTELNETProto OBJECT-TYPE
	SYNTAX     Integer32 (1|2)
	MAX-ACCESS read-write
	STATUS     current
	DESCRIPTION
		"MAC-Telnet Service Protocol
		 1 - MAC-Telnet
		 2 - MAC-SSH
		 Device Allocation: AP,SM"
	DEFVAL { 1 }
	::= { mactelnet 2 }

cambiumLicenseServerEnable OBJECT-TYPE
	SYNTAX     Integer32 (0|1)
	MAX-ACCESS not-accessible
	STATUS     obsolete
	DESCRIPTION
		"Enable License Server Connector
		 0 - Disable,
		 1 - Enable
		 Device Allocation: AP"
	DEFVAL { 1 }
	::= { licensed 1 }

cambiumLicenseServerCloudLicensingID OBJECT-TYPE
	SYNTAX     DisplayString
	MAX-ACCESS not-accessible
	STATUS     obsolete
	DESCRIPTION
		"Cambium Cloud Licensing Identification number. Used for AP identification on the Licensing Server.
		 Device Allocation: AP"
	::= { licensed 2 }

cambiumLicenseServerStatus OBJECT-TYPE
	SYNTAX     Integer32 (-1|0|1|2|2001..2034)
	MAX-ACCESS not-accessible
	STATUS     obsolete
	DESCRIPTION
		"Status of License Server Connector or error code from License Server
		 -1 - Unknown,
		 0 - Connecting to License Server,
		 1 - Connected. ePMP Elevate Subscriber Module Limit synced with License Server,
		 2 - Connected. ePMP Elevate Subscriber Module Limit Exceeded,
		 2004 - Units are not supported with limited concurrency,
		 2012 - Not authorized to process any request,
		 2015 - Internal error,
		 2018 - License is expired,
		 2019 - License is disabled,
		 2023 - License does not exist or license is not in active state,
		 2024 - Invalid parameter,
		 2025 - Session terminated,
		 2026 - Access denied to the requested feature,
		 2031 - No authorization server mapped to given vendorId
		 Device Allocation: AP"
	::= { licensed 3 }

cambiumLicenseServerRefreshFail OBJECT-TYPE
	SYNTAX     Integer32
	MAX-ACCESS not-accessible
	STATUS     obsolete
	DESCRIPTION
		"Counter of consecutive failures on License Server allocation refresh.
		 Refresh request is made at some intervals (each 20 minutes).
		 Device Allocation: AP"
	::= { licensed 4 }

cambiumLicenseServerUpdateFail OBJECT-TYPE
	SYNTAX     Integer32
	MAX-ACCESS not-accessible
	STATUS     obsolete
	DESCRIPTION
		"Counter of consecutive failures on License Server allocation request.
		 Allocation request is made either after reboot or when number of
		 connected SMs is changed.
		 Device Allocation: AP"
	::= { licensed 5 }

cambiumLicenseServerProxyEnable OBJECT-TYPE
	SYNTAX     Integer32 (0|1)
	MAX-ACCESS not-accessible
	STATUS     obsolete
	DESCRIPTION
		"Enable License Server Proxy
		 0 - Disable,
		 1 - Enable
		 Device Allocation: AP"
	DEFVAL { 0 }
	::= { licensed 6 }

cambiumLicenseServerProxyIP OBJECT-TYPE
	SYNTAX     IpAddress
	MAX-ACCESS not-accessible
	STATUS     obsolete
	DESCRIPTION
		"Ip address of proxy server for connection with Licensing Server.
		 Device Allocation: AP"
	::= { licensed 7 }

cambiumLicenseServerProxyPort OBJECT-TYPE
	SYNTAX     Integer32 (1..65535)
	MAX-ACCESS not-accessible
	STATUS     obsolete
	DESCRIPTION
		"Port of proxy server for connection with Licensing Server.
		 Device Allocation: AP"
	DEFVAL { 8080 }
	::= { licensed 8 }

spectralEnable OBJECT-TYPE
	SYNTAX     Integer32 (0|1)
	MAX-ACCESS read-write
	STATUS     current
	DESCRIPTION
		"Enable Spectrum Analyzer
		 0 - Disable,
		 1 - Enable"
	DEFVAL { 0 }
	::= { cambiumSpectral 1 }

watchdogEnable OBJECT-TYPE
	SYNTAX		Integer32 (0|1)
	MAX-ACCESS	read-write
	STATUS		current
	DESCRIPTION
		"Enable Watchdog
			0 - Disable,
			1 - Enable"
	DEFVAL { 0 }
	::= { cambiumWatchdog 1 }

watchdogMode OBJECT-TYPE
	SYNTAX		Integer32 (1..4)
	MAX-ACCESS	read-write
	STATUS		current
	DESCRIPTION
		"Watchdog action on failed ping test:
			1 - Wireless driver restart,
			2 - Ethernet driver restart,
			3 - Radio reboot,
			4 - Wireless driver restart with stats collection"
	DEFVAL { 1 }
	::= { cambiumWatchdog 2 }

watchdogTargetIPAddress OBJECT-TYPE
	SYNTAX		OCTET STRING (SIZE(0..128))
	MAX-ACCESS	read-write
	STATUS		current
	DESCRIPTION
		"Target IP address to be pinged by watchdog."
	::= { cambiumWatchdog 3 }

watchdogPingInterval OBJECT-TYPE
	SYNTAX		Integer32 (1..60)
	MAX-ACCESS	read-write
	STATUS		current
	DESCRIPTION
		"Interval between watchdog ping checks
		 in minutes."
	DEFVAL { 10 }
	::= { cambiumWatchdog 4 }

watchdogPingRetries OBJECT-TYPE
	SYNTAX		Integer32 (3..30)
	MAX-ACCESS	read-write
	STATUS		current
	DESCRIPTION
		"Number of unsuccessfull ping attempts
		 before considering ping check failed."
	DEFVAL { 4 }
	::= { cambiumWatchdog 5 }

crashReporterEnable OBJECT-TYPE
	SYNTAX		Integer32 (0|1|2)
	MAX-ACCESS	read-write
	STATUS		current
	DESCRIPTION
		"Enable Crash Reporter
			0 - Disable,
			1 - Enable,
			2 - None"
	DEFVAL { 2 }
	::= { cambiumCrashReporter 1 }

watchdogGPSAllowHardReset OBJECT-TYPE
	SYNTAX		Integer32 (0|1)
	MAX-ACCESS	read-write
	STATUS		current
	DESCRIPTION
		"Allow GPS watchdog to perform external
		 hardware reset during GPS full reset.
		 0 - Disallow,
		 1 - Allow
		 Device Allocation: AP"
	DEFVAL { 0 }
	::= { watchdogGPS 1 }

watchdogRFEnable OBJECT-TYPE
	SYNTAX		Integer32 (0|1)
	MAX-ACCESS	read-write
	STATUS		current
	DESCRIPTION
		"Allow RF watchdog to perform interface
		 restart.
		 0 - Disable,
		 1 - Enable
		 Device Allocation: AP, SM"
	DEFVAL { 0 }
	::= { watchdogRF 1 }

watchdogRFRSSIThreshold OBJECT-TYPE
	SYNTAX		Integer32 (9..60)
	MAX-ACCESS	read-write
	STATUS		current
	DESCRIPTION
		"RF watchdog RSSI difference
		 threshold.
		 Device Allocation: AP, SM"
	DEFVAL { 20 }
	::= { watchdogRF 2 }

watchdogRFSNRThreshold OBJECT-TYPE
	SYNTAX		Integer32 (9..60)
	MAX-ACCESS	read-write
	STATUS		current
	DESCRIPTION
		"RF watchdog SNR difference
		 threshold.
		 Device Allocation: AP, SM"
	DEFVAL { 20 }
	::= { watchdogRF 3 }

watchdogRFCountThreshold OBJECT-TYPE
	SYNTAX		Integer32 (0..65535)
	MAX-ACCESS	read-write
	STATUS		current
	DESCRIPTION
		"RF watchdog count threshold
		 for raising interface restart
		 Device Allocation: AP, SM"
	DEFVAL { 5 }
	::= { watchdogRF 4 }

cambiumChannelBondingEnable OBJECT-TYPE
	SYNTAX     Integer32 (0|1)
	MAX-ACCESS read-write
	STATUS     current
	DESCRIPTION
		"Enable Channel Bonding
		 0 - Disable,
		 1 - Enable
		 Device Allocation: AP, SM
		 Supported Devices: PTP550"
	DEFVAL { 0 }
	::= { bonding 1 }

cambiumAccelerationEngine OBJECT-TYPE
	SYNTAX     Integer32 (1..3)
	MAX-ACCESS read-write
	STATUS     current
	DESCRIPTION
		"Acceleration engine mode:
		 1 - Automatic selection. In this mode, ECM will detect board type
			to see if NSS acceleration engine is supported. If yes,
			NSS front end will be selected to run. Otherwise SFE front end
			will be selected to run,
		 2 - NSS front end (HW acceleration),
		 3 - SFE front end (SW acceleration)"
	::= { accelerationEngine 1 }

snmpReadOnlyCommunity  OBJECT-TYPE
	SYNTAX	   DisplayString
	MAX-ACCESS read-write
	STATUS	   current
	DESCRIPTION
		"SNMP read-only community name
		Device Allocation: AP, SM"
	DEFVAL	{ "public" }
	::= { snmp 1 }

snmpReadWriteCommunity	OBJECT-TYPE
	SYNTAX	   DisplayString
	MAX-ACCESS read-write
	STATUS	   current
	DESCRIPTION
		"SNMP read-write community name.
		Only private community can read this attribute.
		Device Allocation: AP, SM"
	DEFVAL	{ "private" }
	::= { snmp 2 }

snmpSystemName	OBJECT-TYPE
	SYNTAX	   DisplayString
	MAX-ACCESS read-write
	STATUS	   current
	DESCRIPTION
		"SNMP System Name
		Device Allocation: AP, SM"
	DEFVAL	{ "CambiumNetworks" }
	::= { snmp 3 }

snmpSystemDescription  OBJECT-TYPE
	SYNTAX	   DisplayString
	MAX-ACCESS read-write
	STATUS	   current
	DESCRIPTION
		"SNMP System Description
		Device Allocation: AP, SM"
	::= { snmp 4 }

snmpTrapEnable	OBJECT-TYPE
	SYNTAX	   Integer32 (0|1)
	MAX-ACCESS read-write
	STATUS	   current
	DESCRIPTION
		"SNMP Trap Support Enable
			0 - Disable,
			1 - Enable
		Device Allocation: AP, SM"
	DEFVAL	{ 0 }
	::= { snmp 5 }

snmpTrapCommunity  OBJECT-TYPE
	SYNTAX	   DisplayString
	MAX-ACCESS read-write
	STATUS	   current
	DESCRIPTION
		"SNMP Trap Community
		Device Allocation: AP, SM"
	::= { snmp 6 }

snmpTrapTable  OBJECT-TYPE
	SYNTAX SEQUENCE OF SNMPTrapEntry
	MAX-ACCESS not-accessible
	STATUS	   current
	DESCRIPTION
		"SNMP Trap Servers Table
		Device Allocation: AP, SM"
	::= { snmp 7 }

snmpTrapEntry  OBJECT-TYPE
	SYNTAX	SNMPTrapEntry
	MAX-ACCESS not-accessible
	STATUS	   current
	DESCRIPTION
		"SNMP Trap Table Entry
		Device Allocation: AP, SM"
	INDEX	{ snmpTrapEntryIndex }
	::= { snmpTrapTable 1 }

SNMPTrapEntry ::= SEQUENCE {
	snmpTrapEntryIndex
		Integer32,
	snmpTrapEntryIP
		IpAddress,
	snmpTrapEntryPort
		Integer32
}

snmpTrapEntryIndex OBJECT-TYPE
	SYNTAX	   Integer32 (0..4)
	MAX-ACCESS read-write
	STATUS	   current
	DESCRIPTION
		"SNMP Trap Server IP Table Index
		Table Entry is cleared if Index is set to zero
		Device Allocation: AP, SM"
	::= { snmpTrapEntry 1 }

snmpTrapEntryIP OBJECT-TYPE
	SYNTAX	   IpAddress
	MAX-ACCESS read-write
	STATUS	   current
	DESCRIPTION
		"SNMP Trap Server IP Address
		Device Allocation: AP, SM"
	::= { snmpTrapEntry 2 }

snmpTrapEntryPort OBJECT-TYPE
	SYNTAX	   Integer32 (0..65535)
	MAX-ACCESS read-write
	STATUS	   current
	DESCRIPTION
		"SNMP Trap Server Port Number
		Device Allocation: AP, SM"
	DEFVAL	{ 162 }
	::= { snmpTrapEntry 3 }

snmpDomainAccessEnable	OBJECT-TYPE
	SYNTAX	   Integer32 (0|1)
	MAX-ACCESS read-write
	STATUS	   current
	DESCRIPTION
		"SNMP Access Domain Enable
			0 - Disable,
			1 - Enable
		Device Allocation: AP, SM"
	DEFVAL	{ 0 }
	::= { snmp 8 }

snmpDomainAccessIP OBJECT-TYPE
	SYNTAX	   DisplayString(SIZE(0|7..15))
	MAX-ACCESS read-write
	STATUS	   current
	DESCRIPTION
		"SNMP Access Domain IP Address
		Device Allocation: AP, SM"
	::= { snmp 9 }

snmpDomainAccessIPMask OBJECT-TYPE
	SYNTAX	   DisplayString(SIZE(0|7..15))
	MAX-ACCESS read-write
	STATUS	   current
	DESCRIPTION
		"SNMP Access Domain IP Mask
		Device Allocation: AP, SM"
	::= { snmp 10 }

snmpProtocolVersion OBJECT-TYPE
	SYNTAX     Integer32 (1..3)
	MAX-ACCESS read-write
	STATUS     current
	DESCRIPTION
		"SNMP protocol versions support:
			1 - v1, v2c
			2 - v3
			3 - v1, v2c, v3
		 Device Allocation: AP, SM"
	DEFVAL { 1 }
	::= { snmp 11 }

snmpAgentPort OBJECT-TYPE
	SYNTAX	   Integer32 (1..65535)
	MAX-ACCESS read-write
	STATUS	   current
	DESCRIPTION
		"SNMP Agent Port
		Device Allocation: AP, SM"
	DEFVAL { 161 }
	::= { snmp 12 }

snmpRemoteAccess OBJECT-TYPE
	SYNTAX	   Integer32 (0|1)
	MAX-ACCESS read-write
	STATUS	   current
	DESCRIPTION
		"SNMP Remote Access
			0 - Disable,
			1 - Enable
		Device Allocation: AP, SM"
	DEFVAL	{ 0 }
	::= { snmp 13 }

snmpLinkTrapEnable OBJECT-TYPE
	SYNTAX	   Integer32 (0|1)
	MAX-ACCESS read-write
	STATUS	   current
	DESCRIPTION
		"SNMP Interface Link Up/Down Trap Enable
			0 - Disable,
			1 - Enable
		Device Allocation: AP, SM"
	DEFVAL	{ 0 }
	::= { snmp 14 }

snmpv3UsersTable OBJECT-TYPE
	SYNTAX     SEQUENCE OF Snmpv3UsersEntry
	MAX-ACCESS not-accessible
	STATUS     current
	DESCRIPTION
		"This table contains users for SNMP v3 access
		 Device Allocation: AP, SM"
	::= { snmp 20 }

snmpv3UsersEntry OBJECT-TYPE
	SYNTAX     Snmpv3UsersEntry
	MAX-ACCESS not-accessible
	STATUS     current
	DESCRIPTION
		"User for SNMP v3 access data
		 Device Allocation: AP, SM"
	INDEX	{ snmpv3UsersTableIndex }
	::= { snmpv3UsersTable 1 }

Snmpv3UsersEntry ::= SEQUENCE {
	snmpv3UsersTableIndex	Integer32,
	snmpv3UserName			DisplayString,
	snmpv3UserPassPhrase	DisplayString,
	snmpv3UserSecurityLevel	Integer32,
	snmpv3UserRWAccess		Integer32,
	snmpv3UserAuthMethod	Integer32,
	snmpv3UserEncryption	Integer32
}

snmpv3UsersTableIndex OBJECT-TYPE
	SYNTAX     Integer32 (0..16)
	MAX-ACCESS read-write
	STATUS     current
	DESCRIPTION
		"SNMP v3 users table index
		 Table Entry is cleared if Index is set to zero
		 Device Allocation: AP, SM"
	::= { snmpv3UsersEntry 1 }

snmpv3UserName OBJECT-TYPE
	SYNTAX     DisplayString (SIZE(1..64))
	MAX-ACCESS read-write
	STATUS     current
	DESCRIPTION
		"SNMP v3 user name
		 Device Allocation: AP, SM"
	::= { snmpv3UsersEntry 2 }

snmpv3UserPassPhrase OBJECT-TYPE
	SYNTAX     DisplayString (SIZE(8..64))
	MAX-ACCESS read-write
	STATUS     current
	DESCRIPTION
		"SNMP v3 user passphrase
		 Device Allocation: AP, SM"
	::= { snmpv3UsersEntry 3 }

snmpv3UserSecurityLevel OBJECT-TYPE
	SYNTAX     Integer32 (1..3)
	MAX-ACCESS read-write
	STATUS     current
	DESCRIPTION
		"SNMP v3 user security level:
			1 - noAuthNoPriv
			2 - authNoPriv
			3 - authPriv
		 Device Allocation: AP, SM"
	DEFVAL { 1 }
	::= { snmpv3UsersEntry 4 }

snmpv3UserRWAccess OBJECT-TYPE
	SYNTAX     Integer32 (0|1)
	MAX-ACCESS read-write
	STATUS     current
	DESCRIPTION
		"SNMP v3 user R/W access:
			0 - disable
			1 - enable
		 Device Allocation: AP, SM"
	DEFVAL { 0 }
	::= { snmpv3UsersEntry 5 }

snmpv3UserAuthMethod OBJECT-TYPE
	SYNTAX     Integer32 (1|2)
	MAX-ACCESS read-write
	STATUS     current
	DESCRIPTION
		"SNMP v3 user authentication method:
			1 - MD5
			2 - SHA1
		 Device Allocation: AP, SM"
	DEFVAL { 2 }
	::= { snmpv3UsersEntry 6 }

snmpv3UserEncryption OBJECT-TYPE
	SYNTAX     Integer32 (1|2)
	MAX-ACCESS read-write
	STATUS     current
	DESCRIPTION
		"SNMP v3 user encryption:
			1 - AES
			2 - DES
		 Device Allocation: AP, SM"
	DEFVAL { 1 }
	::= { snmpv3UsersEntry 7 }

systemConfigTimezone  OBJECT-TYPE
	SYNTAX	   DisplayString
	MAX-ACCESS read-write
	STATUS	   current
	DESCRIPTION
		"Time Zone
		Device Allocation: AP, SM"
	DEFVAL	{ "GMT" }
	::= { systemConfig 1 }

systemConfigDeviceName	OBJECT-TYPE
	SYNTAX	   DisplayString (SIZE(0|1..128))
	MAX-ACCESS read-write
	STATUS	   current
	DESCRIPTION
		"SM Device Name
		Device Allocation: AP, SM"
	DEFVAL	{ "Cambium-STA" }
	::= { systemConfig 2 }

systemConfigETSILicense	 OBJECT-TYPE
	SYNTAX	   DisplayString (SIZE(0..128))
	MAX-ACCESS read-write
	STATUS	   obsolete
	DESCRIPTION
		"ETSI Country Code.
		Set the country code using license key on AP. Visit Cambium Webserver
		to get the license key. The country code set in license key will
		be used to set country code on AP if the key validation pass. This
		parameter is for AP only.
		Device Allocation: AP"
	DEFVAL	{ "ETSIkey" }
	::= { systemConfig 3 }

systemConfigSWLockBit  OBJECT-TYPE
	SYNTAX	   Integer32 (0|1)
	MAX-ACCESS read-only
	STATUS	   current
	DESCRIPTION
		"Software Lock Bit.
		This bit indicates if the Software Lock Bit is set or not.
		If the software bit is set then country code needs to be
		set using License Key from Cambium Webserver
			0 - Bit not Set,
			1 - Bit is set
		Device Allocation: AP, SM"
	DEFVAL	{ 0 }
	::= { systemConfig 4 }

systemConfigHWLockBit  OBJECT-TYPE
	SYNTAX	   Integer32 (0|1)
	MAX-ACCESS read-only
	STATUS	   current
	DESCRIPTION
		"Hardware Lock Bit.
		This bit indicates if the hardware Lock Bit is set or not.
		If the hardware bit is set then country code cannot be changed.
			0 - Bit not Set,
			1 - Bit is set
		Device Allocation: AP, SM"
	DEFVAL	{ 0 }
	::= { systemConfig 5 }

systemDeviceLocLatitude	 OBJECT-TYPE
	SYNTAX	   DisplayString (SIZE(0..128))
	MAX-ACCESS read-write
	STATUS	   current
	DESCRIPTION
		"Device GPS Location Latitude.
		Coordinates of device in (h ddd.ddddd) format.
		Used to display location at Google Maps service.
		Device Allocation: AP, SM"
	::= { systemConfig 6 }

systemDeviceLocLongitude  OBJECT-TYPE
	SYNTAX	   DisplayString (SIZE(0..128))
	MAX-ACCESS read-write
	STATUS	   current
	DESCRIPTION
		"Device GPS Location Longitude.
		Coordinates of device in (h ddd.ddddd) format.
		Used to display location at Google Maps service.
		Device Allocation: AP, SM"
	::= { systemConfig 7 }

systemDeviceLocHeight  OBJECT-TYPE
	SYNTAX	   DisplayString (SIZE(0..128))
	MAX-ACCESS read-write
	STATUS	   current
	DESCRIPTION
		"Device GPS Location Longitude.
		Altitude of device above/below mean sea level.
		Device Allocation: AP, SM"
	::= { systemConfig 8 }

-- skip systemConfig 9 for GPSKey License

systemConfigisGPSkeyOK  OBJECT-TYPE
	SYNTAX     Integer32 (0|1)
	MAX-ACCESS read-only
	STATUS     obsolete
	DESCRIPTION
		"GPS Lock.
		This field indicates if the GPS Key is OK. Based on this the GPS
		is locked on the board.
			0 - GPS Key is bad. Sync Source defaulted to Internal GPS only
			1 - GPS Key is good. User can set sync source to any value
		Device Allocation: AP"
	DEFVAL  { 0 }
	::= { systemConfig 10 }

systemConfigGPSLockBit  OBJECT-TYPE
	SYNTAX     Integer32 (0..2)
	MAX-ACCESS read-only
	STATUS     obsolete
	DESCRIPTION
		"GPS Lock Bit.
		This bit indicates if the GPS feature Lock Bit is set or not.
		If the hardware bit is set then GPS synchronisation can't be used.
			0 - No limitation of usage GPS synchronisation,
			1 - GPS synchronisation not allowed,
			2 - The GPSkey required to allow synchronisation
		Device Allocation: AP"
	DEFVAL  { 0 }
	::= { systemConfig 11 }

systemConfigSMLockBit  OBJECT-TYPE
	SYNTAX     Integer32 (0..2)
	MAX-ACCESS read-only
	STATUS     current
	DESCRIPTION
		"SM Lock Bit
		This bit indicates if the AP is locked for Maximum SM registrations support.
		If the bit is set then maximum of 10 SMs can be registered on the AP.
			0 - No limitation, up to 120 SM registrations are supported,
			1 - AP is tiered with 10 SM registrations
		Device Allocation: AP"
	DEFVAL  { 0 }
	::= { systemConfig 12 }

systemConfigSMLimit  OBJECT-TYPE
	SYNTAX     Integer32 (0..120)
	MAX-ACCESS read-only
	STATUS     current
	DESCRIPTION
		"SM Registrations limit, based on Operational License content.
		Indicates the maximum number of SMs with could be registered to an AP.
		Valid only in TDD mode if device is AP Lite.
		Device Allocation: AP"
	DEFVAL  { 0 }
	::= { systemConfig 13 }

cambiumePMPElevateHWLicenseLimit  OBJECT-TYPE
	SYNTAX	   Integer32 (0..120)
	MAX-ACCESS read-only
	STATUS	   current
	DESCRIPTION
		"ePMP Elevate STA according to the license
		Device Allocation: AP"
	DEFVAL	{ 0 }
	::= { systemConfig 14 }

powerSequenceFactoryDefault OBJECT-TYPE
	SYNTAX	   Integer32 (0|1)
	MAX-ACCESS read-write
	STATUS	   current
	DESCRIPTION
		"Set this to enable or disable the ability to factory default the radio's
		configuration using the power cycle sequence(explained in the User Guide).
			0 - Disabled
			1 - Enabled
		Device Allocation: AP, SM"
	DEFVAL	{ 1 }
	::= { systemConfig 15 }

systemConfigLockedCC OBJECT-TYPE
	SYNTAX	   DisplayString (SIZE(0|1..2))
	MAX-ACCESS read-only
	STATUS	   current
	DESCRIPTION
		"Return Locked Country Value in case if device is locked for particular country.
		Device Allocation: AP, SM"
	::= { systemConfig 16 }

systemConfigMinAntGain OBJECT-TYPE
	SYNTAX	   Integer32 (0..40)
	MAX-ACCESS read-only
	STATUS	   current
	DESCRIPTION
		"Return Minimum allowed Antenna Gain.
		Device Allocation: AP, SM"
	::= { systemConfig 17 }

systemConfigOperationalLicense OBJECT-TYPE
	SYNTAX	   DisplayString (SIZE(0..128))
	MAX-ACCESS read-write
	STATUS	   current
	DESCRIPTION
		"Device Operational License.
		Set Operational License on AP to extend basic functionality.
		Visit Cambium Webserver to get the license key. ETSI country code and
		maximum SMs count value will be set on AP if the key validation pass.
		License is required on locked devices only.
		Device Allocation: AP"
	::= { systemConfig 18 }

systemConfigIPv6Support OBJECT-TYPE
	SYNTAX     Integer32 (0|1)
	MAX-ACCESS read-write
	STATUS     current
	DESCRIPTION
		"Systemwide IPv6 support.
		Enables Systemwide IPv6 support:
			0 - IPv6 Support Disabled,
			1 - IPv6 Support Enabled,
		Device Allocation: AP, SM"
	::= { systemConfig 19 }

systemConfigFactoryResetKeepPwd OBJECT-TYPE
	SYNTAX	   Integer32 (0|1)
	MAX-ACCESS read-write
	STATUS	   current
	DESCRIPTION
		"Keep Passwords after Factory Default
			0 - Disabled
			1 - Enabled
		Device Allocation: AP, SM"
	DEFVAL	{ 0 }
	::= { systemConfig 20 }

cambiumDeviceNameLoginDisplay OBJECT-TYPE
	SYNTAX     Integer32 (0|1)
	MAX-ACCESS read-write
	STATUS     current
	DESCRIPTION
		"Displaying the device name (id) in an login state for web GUI
			1 - display
			0 - don`t display"
	DEFVAL  { 1 }
	::= { systemConfig 21 }

systemConfigStartDHT OBJECT-TYPE
	SYNTAX	   Integer32 (-45..70)
	MAX-ACCESS read-write
	STATUS	   current
	DESCRIPTION
		"Begin value of dynamic heating temperature (-45 .. 70)"
	DEFVAL	{ -5 }
	::= { systemConfig 22 }

systemConfigStopDHT OBJECT-TYPE
	SYNTAX	   Integer32 (-45..70)
	MAX-ACCESS read-write
	STATUS	   current
	DESCRIPTION
		"End value of dynamic heating temperature (-45 .. 70)"
	DEFVAL	{ 5 }
	::= { systemConfig 23 }

systemConfigPreheatStopTemp OBJECT-TYPE
	SYNTAX	   Integer32 (-45..40)
	MAX-ACCESS read-only
	STATUS	   current
	DESCRIPTION
		"Preheat stop temperature (-45 .. 40)"
	DEFVAL	{ -5 }
	::= { systemConfig 24 }

systemConfigPreheatStopTimeout OBJECT-TYPE
	SYNTAX	   Integer32 (0..240)
	MAX-ACCESS read-only
	STATUS	   current
	DESCRIPTION
		"Preheat stop timeout (0 .. 240)"
	DEFVAL	{ 20 }
	::= { systemConfig 25 }

systemConfigBIB  OBJECT-TYPE
	SYNTAX     Integer32 (0..16)
	MAX-ACCESS read-only
	STATUS     current
	DESCRIPTION
		"BIB Lock value in Dec.
		This OID displays locking information for the BIB (Bridge in the Box) feature.
		If BIB lock is set then device is considered to be a BIB product:
			0x00 or 0xff - No BIB Locks are set,
			0x01 - 0x0F -> Bridge in a Box for AP,
			0x11 - 0x1F -> Bridge in a Box for SM,
			0x10 - cnVision SM Feature Lock.
		Device Allocation: AP, SM"
	DEFVAL  { 0 }
	::= { systemConfig 26 }

systemConfigLanguage  OBJECT-TYPE
	SYNTAX     DisplayString(SIZE(2))
	MAX-ACCESS read-write
	STATUS     current
	DESCRIPTION
		"System Language - GUI/CLI System language.
			Major locales include:
			ar - Arabic
			bn - Bengali/Bangladesh
			de - German
			en - English
			es - Spanish
			fr - French
			hi - Hindi
			it - Italian
			ja - Japanese
			pt - Portuguese
			ru - Russian
			zh - Chinese
		Device Allocation: AP, SM"
	DEFVAL  { "en" }
	::= { systemConfig 27 }

systemConfigCNVision  OBJECT-TYPE
	SYNTAX	   Integer32 (0|1)
	MAX-ACCESS read-only
	STATUS	   current
	DESCRIPTION
		"cnVision Lock Bit.
		This bit indicates if cnVision Lock Bit is set or not.
		If cnVision lock bit is set then device is considered to be a CCTV product:
			0 - cnVision Bit not Set,
			1 - cnVision Bit is set
		Device Allocation: AP, SM"
	DEFVAL	{ 0 }
	::= { systemConfig 28 }

systemConfigSCLockBit OBJECT-TYPE
	SYNTAX     Integer32 (0|1)
	MAX-ACCESS read-only
	STATUS     current
	DESCRIPTION
		"Soft Country Lock Bit.
		 This bit indicates if the systemConfigLockedCC value can be
		 overridden using a valid Operational License:
			0 - Soft Country Lock feature is disabled,
			1 - Soft Country Lock feature is enabled.
		Device Allocation: AP"
	DEFVAL	{ 0 }
	::= { systemConfig 29 }

systemNtpServerIPMode OBJECT-TYPE
	SYNTAX	   Integer32 (1|2)
	MAX-ACCESS read-write
	STATUS	   current
	DESCRIPTION
		"NTP Server IP Address receive mode
			1 - Static,
			2 - DHCP
		Device Allocation: AP, SM"
	DEFVAL	{ 2 }
	::= { systemNtpServer 1 }

systemNtpServerPrimaryIP  OBJECT-TYPE
	SYNTAX	   DisplayString (SIZE(0|1..128))
	MAX-ACCESS read-write
	STATUS	   current
	DESCRIPTION
		"NTP Server 1 IP Address or Hostname
		Device Allocation: AP, SM"
	::= { systemNtpServer 2 }

systemNtpServerSecondaryIP	OBJECT-TYPE
	SYNTAX	   DisplayString (SIZE(0|1..128))
	MAX-ACCESS read-write
	STATUS	   current
	DESCRIPTION
		"NTP Server 2 IP Address or Hostname
		Device Allocation: AP, SM"
	::= { systemNtpServer 3 }

webService OBJECT-TYPE
	SYNTAX	   Integer32 (1|2|3)
	MAX-ACCESS read-write
	STATUS	   current
	DESCRIPTION
		"Web Service
			1 - HTTP,
			2 - HTTPS,
			3 - HTTP and HTTPS
		Device Allocation: AP, SM"
	DEFVAL	{ 3 }
	::= { cambiumWebServer 1 }

httpPort  OBJECT-TYPE
	SYNTAX	   Integer32 (0..65535)
	MAX-ACCESS read-write
	STATUS	   current
	DESCRIPTION
		"HTTP Port
		Device Allocation: AP, SM"
	DEFVAL	{ 80 }
	::= { cambiumWebServer 2 }

httpsPort  OBJECT-TYPE
	SYNTAX	   Integer32 (0..65535)
	MAX-ACCESS read-write
	STATUS	   current
	DESCRIPTION
		"HTTPs Port"
	DEFVAL	{ 443 }
	::= { cambiumWebServer 3 }

uhttpdMainPem  OBJECT-TYPE
	SYNTAX	   OCTET STRING (SIZE(0..8192))
	MAX-ACCESS read-write
	STATUS	   current
	DESCRIPTION
		"Uhttpd .pem file
		Device Allocation: AP, SM"
	::= { cambiumWebServer 4 }

uhttpdMainInactLogout  OBJECT-TYPE
	SYNTAX	   Integer32 (0|1)
	MAX-ACCESS read-write
	STATUS	   current
	DESCRIPTION
		"Web Interface Inactivity Logout:
		1 - Enable automatic user logout from Web UI after predefined inactivity timeout,
		2 - Disable automatic user logout from Web UI after predefined inactivity timeout
		Device Allocation: AP, SM"
	DEFVAL  { 1 }
	::= { cambiumWebServer 5 }

wirelessDeviceCountryCode  OBJECT-TYPE
	SYNTAX	   DisplayString (SIZE(0|2))
	MAX-ACCESS read-write
	STATUS	   current
	DESCRIPTION
		"Country Code.
		If US Lock SKU, this is US and cannot be changed.
		If not locked, for 9350, it will be None, for 9344, it will be Follow AP CC.
		When user change CC at SM, the SM Scan Frequency Type  will be FA
		Device Allocation: AP"
	DEFVAL	{ "NS" }
	::= { wirelessDevice 1 }

wirelessType  OBJECT-TYPE
	SYNTAX	   Integer32 (1|2)
	MAX-ACCESS read-write
	STATUS	   obsolete
	DESCRIPTION
		"Wireless type:
			1 - tdd driver,
			2 - 80211 (aquila) driver
		Device Allocation: AP, SM"
	DEFVAL	{ 1 }
	::= { wirelessDevice 2 }

wirelessDefaultCountryCode	OBJECT-TYPE
	SYNTAX	   DisplayString (SIZE(0|2))
	MAX-ACCESS read-write
	STATUS	   current
	DESCRIPTION
		"Default Country Code."
	DEFVAL	{ "OT" }
	::= { wirelessDevice 3 }

wirelessSmartAntennaEnabled	OBJECT-TYPE
	SYNTAX	   Integer32 (0|1)
	MAX-ACCESS read-write
	STATUS	   current
	DESCRIPTION
		"Enable/Disable SmartAntenna"
	DEFVAL	{ 0 }
	::= { wirelessDevice 4 }

wirelessAPForcedSector  OBJECT-TYPE
	SYNTAX     Integer32 (0|1|2)
	MAX-ACCESS read-write
	STATUS     current
	DESCRIPTION
		"Enable/Disable Forcing of Sector/Smart Antenna for all SMs.
		0 - auto mode (default)
		1 - force sector antenna
		2 - force Smart antenna
		Device Allocation: AP"
	DEFVAL  { 0 }
	::= { wirelessDevice 5 }

wirelessSTAForcedSector  OBJECT-TYPE
	SYNTAX     Integer32 (0|1|2)
	MAX-ACCESS read-write
	STATUS     current
	DESCRIPTION
		"Enable/Disable Forcing of Sector/Smart Antenna for current SM.
		0 - auto mode (default)
		1 - force sector antenna
		2 - force Smart antenna
		Device Allocation: STA"
	DEFVAL  { 0 }
	::= { wirelessDevice 6 }

wirelessMUMIMOEnable	OBJECT-TYPE
	SYNTAX	Integer32 (2|3)
	MAX-ACCESS	read-write
	STATUS	current
	DESCRIPTION
		"AP Antenna for MU-MIMO:
			2 - Sector
			3 - Omni
			Applicable for: ePMP 3000
		Device Allocation: AP"
	DEFVAL  { 2 }
	::= { wirelessDevice 10 }

wirelessMUMIMOSoundingInterval	OBJECT-TYPE
	SYNTAX	Integer32 (1..100)
	MAX-ACCESS	read-write
	STATUS	current
	DESCRIPTION
		"Sounding Interval:
		Sounding period in seconds
		Applicable for: ePMP 3000
		Device Allocation: AP"
	DEFVAL	{ 1 }
	::= { wirelessDevice 11 }

wirelessMUMIMOSoundingAzimuthCycle	OBJECT-TYPE
	SYNTAX	Integer32 (1..10000)
	MAX-ACCESS	read-write
	STATUS	current
	DESCRIPTION
		"Sounding Azimuth Cycle:
		Number of Sounding Periods
		Applicable for: ePMP 3000
		Device Allocation: AP"
	DEFVAL  { 60 }
	::= { wirelessDevice 12 }

wirelessMUMIMOCBFRateAdapt	OBJECT-TYPE
	SYNTAX	Integer32 (0|1)
	MAX-ACCESS	read-write
	STATUS	current
	DESCRIPTION
		"Flag to disable/enable the CBF
		rate adaptation
			0 - Disabled
			1 - Enabled
		Device Allocation: AP(ePMP3000)"
	DEFVAL  { 1 }
	::= { wirelessDevice 13 }

wirelessMUMIMOCBFRateAdaptIndex	OBJECT-TYPE
	SYNTAX	Integer32 (0..7)
	MAX-ACCESS	read-write
	STATUS	current
	DESCRIPTION
		"Index for starting CBF rate
		which will be the only CBF rate
		used if RA is disabled
		Device Allocation: AP(ePMP3000)"
	DEFVAL  { 7 }
	::= { wirelessDevice 14 }

wirelessRandFD	OBJECT-TYPE
	SYNTAX	Integer32 (0|1)
	MAX-ACCESS	read-write
	STATUS	current
	DESCRIPTION
		"Enable random frame duration shifting"
	DEFVAL  { 0 }
	::= { wirelessDevice 15 }

wirelessEPTPPPDUDuration	OBJECT-TYPE
	SYNTAX	Integer32 (1000|2000|4000)
	MAX-ACCESS	read-write
	STATUS	obsolete
	DESCRIPTION
		"max PPDU duration
		for ePTP mode
		802.11ac  only
		Device Allocation: AP, SM"
	DEFVAL  { 2000 }
	::= { wirelessDevice 16 }

wirelessRadioTransmissionOptimization	OBJECT-TYPE
	SYNTAX	Integer32 (1..3)
	MAX-ACCESS	read-write
	STATUS	current
	DESCRIPTION
		"Radio transmission optimization
			1 - lower latency - Radio transmission optimized to achieve minimum latency
			2 - balanced - Default mode of operation
			3 - higher throughput - Radio transmission optimized to achieve the best throughput numbers
		Only for ePTP mode on the 802.11ac and 802.11ax devices
		Device Allocation: AP"
	DEFVAL  { 2 }
	::= { wirelessDevice 17 }

wirelessInterfaceMode  OBJECT-TYPE
	SYNTAX	   Integer32 (1|2|3)
	MAX-ACCESS read-write
	STATUS	   current
	DESCRIPTION
		"Wireless Interface Mode:
			1 for AP,
			2 for SM,
			3 for Spectrum Analyzer
		Device Allocation: AP, SM"
	::= { wirelessInterface 1 }

wirelessInterfaceSSID  OBJECT-TYPE
	SYNTAX	   OCTET STRING (SIZE(1..32))
	MAX-ACCESS read-write
	STATUS	   current
	DESCRIPTION
		"Wireless SSID
		Device Allocation: AP
		Note: SSID will be automatically reduced down to 30 symbols for Channel Bonding Mode"
	DEFVAL	{ "Cambium-AP" }
	::= { wirelessInterface 2 }

wirelessInterfaceEncryption	 OBJECT-TYPE
	SYNTAX	   Integer32 (1|2|3)
	MAX-ACCESS read-write
	STATUS	   current
	DESCRIPTION
		"Wireless authentication type:
			1 - Open mode,
			2 - wpa2 mode,
			3 - EAP-TTLS
		Device Allocation: AP"
	DEFVAL	{ 2 }
	::= { wirelessInterface 3 }

wirelessInterfaceEncryptionKey	OBJECT-TYPE
	SYNTAX	   OCTET STRING (SIZE(0|8..63))
	MAX-ACCESS read-write
	STATUS	   current
	DESCRIPTION
		"Pre-shared authentication key.
		Only private community can read this attribute.
		Device Allocation: AP"
	DEFVAL	{ "Cam39-Tai!wdmv" }
	::= { wirelessInterface 4 }

wirelessInterfaceHTMode	 OBJECT-TYPE
	SYNTAX	   Integer32 (1..6)
	MAX-ACCESS read-write
	STATUS	   current
	DESCRIPTION
		"Frequency Bandwidth
			1 - 20Mhz,
			2 - 40Mhz,
			3 - 10Mhz,
			4 - 5MHz,
			5 - 80MHz,
			6 - 160MHz
		Device Allocation: AP"
	DEFVAL	{ 1 }
	::= { wirelessInterface 5 }

wirelessInterfaceTXPower  OBJECT-TYPE
	SYNTAX	   Integer32 (-24..33)
	MAX-ACCESS read-write
	STATUS	   current
	DESCRIPTION
		"TX Power (Board Output Conducted)
		In the SM mode this parameter can be changed
		only if wirelessTXPowerManualLimit is 1;
		For ePMP Elevate devices low limit is equal -4;
		For 802.11n Maximum TXPower is equal 30dB
		Device Allocation: AP, SM"
	DEFVAL	{ 7 }
	::= { wirelessInterface 6 }

wirelessInterfaceTDDAntennaGain	 OBJECT-TYPE
	SYNTAX	   Integer32 (0..40)
	MAX-ACCESS read-write
	STATUS	   current
	DESCRIPTION
		"Antenna Gain
		Device Allocation: AP, SM"
	DEFVAL	{ 16 }
	::= { wirelessInterface 7 }

wirelessInterfaceTDDRatio  OBJECT-TYPE
	SYNTAX	   Integer32 (1|2|3|4|35|40|45|55|60|65|70)
	MAX-ACCESS read-write
	STATUS	   current
	DESCRIPTION
		"DL/UL Ratio:
			1  - 75/25,
			2  - 50/50,
			3  - 30/70,
			4  - Flexible,
			35 - 35/65,
			40 - 40/60,
			45 - 45/55,
			55 - 55/45,
			60 - 60/40,
			65 - 65/35,
			70 - 70/30
		Device Allocation: AP"
	DEFVAL	{ 4 }
	::= { wirelessInterface 9 }

wirelessInterfaceTPCTRL	 OBJECT-TYPE
	SYNTAX	   Integer32 (-80..-30)
	MAX-ACCESS read-write
	STATUS	   current
	DESCRIPTION
		"Set/get target receive level (TRL)
		Device Allocation: AP"
	DEFVAL	{ -60 }
	::= { wirelessInterface 10 }

wirelessInterfaceTPCMode  OBJECT-TYPE
	SYNTAX	   Integer32 (0|1|2)
	MAX-ACCESS read-write
	STATUS	   obsolete
	DESCRIPTION
		"Power mode selection.
		Values:0 - Disable, 1 - Open Loop, 2 - Close Loop
		When system is in Fixed mode (75/35, 50/50, 30/70), this parameter can only be Close or Open Loop.
		When system is in Flexible mode, this parameter can be either Close Loop, Open Loop or Disable.
		The default TPC mode is Close Loop.
		Device Allocation: AP"
	DEFVAL	{ 2 }
	::= { wirelessInterface 11 }

wirelessInterfacePTPMode  OBJECT-TYPE
	SYNTAX	   Integer32 (0|1|2)
	MAX-ACCESS read-write
	STATUS	   current
	DESCRIPTION
		"PTP Setting
			0 - Off
			1 - Connect First SM,
			2 - MAC Address Limited
		Device Allocation: AP"
	DEFVAL	{ 1 }
	::= { wirelessInterface 12 }

wirelessInterfacePTPMACAddress	OBJECT-TYPE
	SYNTAX	   DisplayString (SIZE(0|11..17))
	MAX-ACCESS read-write
	STATUS	   current
	DESCRIPTION
		"PTP MAC Address
		Device Allocation: AP"
	::= { wirelessInterface 13 }

wirelessInterfaceSyncSource	 OBJECT-TYPE
	SYNTAX	   Integer32 (1|2|3|4|5)
	MAX-ACCESS read-write
	STATUS	   current
	DESCRIPTION
		"1PPS Sync Source
			1 - GPS,
			2 - CMM4,
			3 - Internal Free Run,
			4 - CMM3,
			5 - CMM5
		Device Allocation: AP"
	DEFVAL	{ 3 }
	::= { wirelessInterface 14 }

wirelessInterfaceSyncHoldTime  OBJECT-TYPE
	SYNTAX	   Integer32 (20..864000)
	MAX-ACCESS read-write
	STATUS	   current
	DESCRIPTION
		"GPS Sync Hold Time in seconds
		Device Allocation: AP"
	DEFVAL	{ 30 }
	::= { wirelessInterface 15 }

wirelessInterfaceScanFrequencyListTwenty  OBJECT-TYPE
	SYNTAX	   DisplayString (SIZE(0|1..1500))
	MAX-ACCESS read-write
	STATUS	   current
	DESCRIPTION
		"Scan Frequency List for 20 MHz
		Device Allocation: SM"
	::= { wirelessInterface 16 }

wirelessInterfaceScanFrequencyListForty	 OBJECT-TYPE
	SYNTAX	   DisplayString (SIZE(0|1..1500))
	MAX-ACCESS read-write
	STATUS	   current
	DESCRIPTION
		"Scan Frequency List for 40 MHz
		Device Allocation: SM"
	::= { wirelessInterface 17 }

centerFrequency	 OBJECT-TYPE
	SYNTAX	   Integer32 (0|2355..7200)
	MAX-ACCESS read-write
	STATUS	   current
	DESCRIPTION
		"Per freq band: 5725 GHz for 5G SKU, 2355 for 2.4G SKU
		Device Allocation: AP"
	::= { wirelessInterface 18 }

dfsAlternative1CenterFrequency	OBJECT-TYPE
	SYNTAX	   Integer32 (0|2355..7200)
	MAX-ACCESS read-write
	STATUS	   current
	DESCRIPTION
		"Per freq band
		Device Allocation: AP"
	::= { wirelessInterface 19 }

dfsAlternative2CenterFrequency	OBJECT-TYPE
	SYNTAX	   Integer32 (0|2355..7200)
	MAX-ACCESS read-write
	STATUS	   current
	DESCRIPTION
		"Per freq band
		Device Allocation: AP"
	::= { wirelessInterface 20 }

wirelessMaximumCellSize	 OBJECT-TYPE
	SYNTAX	   Integer32 (0..200)
	MAX-ACCESS read-write
	STATUS	   current
	DESCRIPTION
		"Maximum Cell Size in units
		wirelessCellSizeUnit defines the unit type:
			1 - Miles
			2 - Kilometers
		Note: for ePMP 1000/2000 devices maximum value is 65 units
		Device Allocation: AP"
	DEFVAL	{ 3 }
	::= { wirelessInterface 21 }

wirelessCellSizeUnit  OBJECT-TYPE
	SYNTAX	   Integer32 (1|2)
	MAX-ACCESS read-write
	STATUS	   current
	DESCRIPTION
		"Maximum Cell Size units:
			1 - Miles
			2 - Kilometers
		Device Allocation: AP"
	::= { wirelessInterface 22 }

wirelessMaximumSTA	OBJECT-TYPE
	SYNTAX	   Integer32 (0|1..120)
	MAX-ACCESS read-write
	STATUS	   current
	DESCRIPTION
		"Maximum Number of SM
		Device Allocation: AP"
	DEFVAL	{ 60 }
	::= { wirelessInterface 23 }

wirelessRadiusTimeout  OBJECT-TYPE
	SYNTAX	   Integer32 (1..20)
	MAX-ACCESS read-write
	STATUS	   current
	DESCRIPTION
		"RADIUS server response timeout.
		Only private community can read this attribute.
		Device Allocation: AP"
	DEFVAL	{ 5 }
	::= { wirelessRadius 1 }

wirelessRadiusRetry	 OBJECT-TYPE
	SYNTAX	   Integer32 (0..5)
	MAX-ACCESS read-write
	STATUS	   current
	DESCRIPTION
		"RADIUS server retry.
		Only private community can read this attribute.
		Device Allocation: AP"
	DEFVAL	{ 1 }
	::= { wirelessRadius 2 }

wirelessRadiusGUIUserAuth  OBJECT-TYPE
	SYNTAX	   Integer32 (0|1|2)
	MAX-ACCESS read-write
	STATUS	   current
	DESCRIPTION
		"SM GUI User Authentication Option
			0 - Device Local Only
			1 - Remote RADIUS Server Only
			2 - Remote RADIUS Server and Fallback to Local
		Only private community can read this attribute.
		Device Allocation: AP"
	DEFVAL	{ 0 }
	::= { wirelessRadius 3 }

wirelessRadiusCurrentGUIUserAuth  OBJECT-TYPE
	SYNTAX	   Integer32 (0|1|2)
	MAX-ACCESS read-only
	STATUS	   obsolete
	DESCRIPTION
		"Current GUI User Authentication Option
			0 - Device Local Only
			1 - Remote RADIUS Server Only
			2 - Remote RADIUS Server and Fallback to Local
		Only private community can read this attribute.
		Device Allocation: SM
		Replaced with status field networkRadiusVSAGUIauthType"
	::= { wirelessRadius 4 }

wirelessRadiusSeverInfo	 OBJECT-TYPE
	SYNTAX	   DisplayString (SIZE(0..128))
	MAX-ACCESS read-only
	STATUS	   current
	DESCRIPTION
		"RADIUS server info.
		Only private community can read this attribute.
		Device Allocation: SM"
	::= { wirelessRadius 5 }

wirelessRadiusIdentityStr  OBJECT-TYPE
	SYNTAX	   DisplayString (SIZE(0..128))
	MAX-ACCESS read-write
	STATUS	   current
	DESCRIPTION
		"Authentication Identity String.
		Only private community can read this attribute.
		Device Allocation: SM"
	DEFVAL	{ "anonymous" }
	::= { wirelessRadius 6 }

wirelessRadiusIdentityRealm	 OBJECT-TYPE
	SYNTAX	   DisplayString (SIZE(0..128))
	MAX-ACCESS read-write
	STATUS	   current
	DESCRIPTION
		"Authentication Identity Realm.
		Only private community can read this attribute.
		Device Allocation: SM"
	DEFVAL	{ "cambiumnetworks.com" }
	::= { wirelessRadius 7 }

wirelessRadiusUsername	OBJECT-TYPE
	SYNTAX	   DisplayString (SIZE(1..128))
	MAX-ACCESS read-write
	STATUS	   current
	DESCRIPTION
		"Authentication Username.
		Only private community can read this attribute.
		Device Allocation: SM"
	DEFVAL	{ "cambium-station" }
	::= { wirelessRadius 8 }

wirelessRadiusPassword	OBJECT-TYPE
	SYNTAX	   OCTET STRING (SIZE(0..128))
	MAX-ACCESS read-write
	STATUS	   current
	DESCRIPTION
		"Authentication Password.
		Only private community can read this attribute.
		Device Allocation: SM"
	DEFVAL	{ "cambium123" }
	::= { wirelessRadius 9 }

useMACAddressAsWirelessRadiusUsername  OBJECT-TYPE
	SYNTAX	   Integer32 (0|1|2)
	MAX-ACCESS read-write
	STATUS	   current
	DESCRIPTION
		"For using an Ethernet MAC address instead of RADIUS username
		 0 - Off (default),
		 1 - using ':' as format,
		 2 - using '-' as format
		Only private community can read this attribute.
		Device Allocation: SM"
	DEFVAL	{ 0 }
	::= { wirelessRadius 10 }

wirelessRadiusServerTable  OBJECT-TYPE
	SYNTAX SEQUENCE OF WirelessRadiusServerEntry
	MAX-ACCESS not-accessible
	STATUS	   current
	DESCRIPTION
		"RADIUS servers table
		Device Allocation: AP"
	::= { wirelessRadiusServerList 1 }

wirelessRadiusServerEntry  OBJECT-TYPE
	SYNTAX	WirelessRadiusServerEntry
	MAX-ACCESS not-accessible
	STATUS	   current
	DESCRIPTION
		"RADIUS servers table entry
		Device Allocation: AP"
	INDEX	{ wirelessRadiusServerIndex }

	::= { wirelessRadiusServerTable 1 }

WirelessRadiusServerEntry ::= SEQUENCE {
	wirelessRadiusServerIndex
		Integer32,
	wirelessRadiusServerIP
		IpAddress,
	wirelessRadiusServerPort
		Integer32,
	wirelessRadiusServerSecret
		OCTET STRING
}

wirelessRadiusServerIndex  OBJECT-TYPE
	SYNTAX	   Integer32 (0..3)
	MAX-ACCESS read-write
	STATUS	   current
	DESCRIPTION
		"RADIUS servers limiting number
		Device Allocation: AP"
	::= { wirelessRadiusServerEntry 1 }

wirelessRadiusServerIP	OBJECT-TYPE
	SYNTAX	   IpAddress
	MAX-ACCESS read-write
	STATUS	   current
	DESCRIPTION
		"RADIUS server IP address
		Device Allocation: AP"
	::= { wirelessRadiusServerEntry 2 }

wirelessRadiusServerPort  OBJECT-TYPE
	SYNTAX	   Integer32(1..65535)
	MAX-ACCESS read-write
	STATUS	   current
	DESCRIPTION
		"RADIUS server port
		Device Allocation: AP"
	DEFVAL	{ 1812 }
	::= { wirelessRadiusServerEntry 3 }

wirelessRadiusServerSecret	OBJECT-TYPE
	SYNTAX	   OCTET STRING (SIZE(0|1..128))
	MAX-ACCESS read-write
	STATUS	   current
	DESCRIPTION
		"RADIUS server port
		Device Allocation: AP"
	::= { wirelessRadiusServerEntry 4 }

wirelessRadiusDefaultCertificate OBJECT-TYPE
	SYNTAX	   OCTET STRING (SIZE(0..8192))
	MAX-ACCESS read-only
	STATUS	   current
	DESCRIPTION
		"Default RADIUS certificate.
		Only private community can read this attribute.
		Device Allocation: SM"
	::= { wirelessRadiusCertificateSet 1 }

wirelessRadiusUser1Certificate OBJECT-TYPE
	SYNTAX	   OCTET STRING (SIZE(0|1..8192))
	MAX-ACCESS read-write
	STATUS	   current
	DESCRIPTION
		"Default RADIUS certificate.
		Only private community can read this attribute.
		Device Allocation: SM"
	::= { wirelessRadiusCertificateSet 2 }

wirelessRadiusUser2Certificate OBJECT-TYPE
	SYNTAX	   OCTET STRING (SIZE(0|1..8192))
	MAX-ACCESS read-write
	STATUS	   current
	DESCRIPTION
		"Default RADIUS certificate.
		Only private community can read this attribute.
		Device Allocation: SM"
	::= { wirelessRadiusCertificateSet 3 }

wirelessRadiusUseDefaultCertificate	 OBJECT-TYPE
	SYNTAX	   Integer32(0|1)
	MAX-ACCESS read-write
	STATUS	   current
	DESCRIPTION
		"RADIUS default certificate use.
		Only private community can read this attribute.
		Device Allocation: SM"
	DEFVAL	{ 1 }
	::= { wirelessRadiusCertificateSet 4 }

wirelessRadiusPMP320Certificate OBJECT-TYPE
	SYNTAX	   OCTET STRING (SIZE(0..8192))
	MAX-ACCESS read-only
	STATUS	   current
	DESCRIPTION
		"PMP320 RADIUS certificate.
		Only private community can read this attribute.
		Device Allocation: SM"
	::= { wirelessRadiusExtraCertificateSet 1 }

wirelessRadiusUsePMP320Certificate	OBJECT-TYPE
	SYNTAX	   Integer32(0|1)
	MAX-ACCESS read-write
	STATUS	   current
	DESCRIPTION
		"RADIUS PMP320 certificate use.
		Only private community can read this attribute.
		Device Allocation: SM"
	DEFVAL	{ 1 }
	::= { wirelessRadiusExtraCertificateSet 2 }

wirelessRadiusPMP450Certificate OBJECT-TYPE
	SYNTAX	   OCTET STRING (SIZE(0..8192))
	MAX-ACCESS read-only
	STATUS	   current
	DESCRIPTION
		"PMP450 RADIUS certificate.
		Only private community can read this attribute.
		Device Allocation: SM"
	::= { wirelessRadiusExtraCertificateSet 3 }

wirelessRadiusUsePMP450Certificate	OBJECT-TYPE
	SYNTAX	   Integer32(0|1)
	MAX-ACCESS read-write
	STATUS	   current
	DESCRIPTION
		"RADIUS PMP450 certificate use.
		Only private community can read this attribute.
		Device Allocation: SM"
	DEFVAL	{ 1 }
	::= { wirelessRadiusExtraCertificateSet 4 }

wirelessRadiusUseDefCertificate	 OBJECT-TYPE
	SYNTAX	   Integer32(0|1)
	MAX-ACCESS read-write
	STATUS	   obsolete
	DESCRIPTION
		"RADIUS default certificate use
		Device Allocation: SM"
	DEFVAL	{ 1 }
	::= { wirelessRadiusCertificateListRow1 1 }

wirelessRadiusUser1CertificateName	OBJECT-TYPE
	SYNTAX	   DisplayString
	MAX-ACCESS read-write
	STATUS	   obsolete
	DESCRIPTION
		"First user RADIUS certificate name
		Device Allocation: AP"
	DEFVAL	{ "cert2" }
	::= { wirelessRadiusCertificateListRow2 1 }

wirelessRadiusUser2CertificateName	OBJECT-TYPE
	SYNTAX	   DisplayString
	MAX-ACCESS read-write
	STATUS	   obsolete
	DESCRIPTION
		"Second user RADIUS certificate name
		Device Allocation: AP"
	DEFVAL	{ "cert3" }
	::= { wirelessRadiusCertificateListRow3 1 }

wirelessRadiusDefCertificateView  OBJECT-TYPE
	SYNTAX	   DisplayString
	MAX-ACCESS read-only
	STATUS	   obsolete
	DESCRIPTION
		"RADIUS default certificate view
		Device Allocation: AP"
	::= { wirelessRadiusCertificateListRow1 2 }

wirelessRadiusUser1CertificateView	OBJECT-TYPE
	SYNTAX	   DisplayString
	MAX-ACCESS read-only
	STATUS	   obsolete
	DESCRIPTION
		"First user RADIUS certificate view
		Device Allocation: AP"
	::= { wirelessRadiusCertificateListRow2 2 }

wirelessRadiusUser2CertificateView	OBJECT-TYPE
	SYNTAX	   DisplayString
	MAX-ACCESS read-only
	STATUS	   obsolete
	DESCRIPTION
		"Second user RADIUS certificate view
		Device Allocation: AP"
	::= { wirelessRadiusCertificateListRow3 2 }

dfsAlternative1Bandwidth  OBJECT-TYPE
	SYNTAX	   Integer32 (1..5)
	MAX-ACCESS read-write
	STATUS	   current
	DESCRIPTION
		"Frequency Bandwidth
			1 - 20Mhz,
			2 - 40Mhz,
			3 - 10Mhz,
			4 - 5Mhz,
			5 - 80 MHz
		Device Allocation: AP"
	DEFVAL	{ 1 }
	::= { wirelessInterface 24 }

dfsAlternative2Bandwidth  OBJECT-TYPE
	SYNTAX	   Integer32 (1..5)
	MAX-ACCESS read-write
	STATUS	   current
	DESCRIPTION
		"Frequency Bandwidth
			1 - 20Mhz,
			2 - 40Mhz,
			3 - 10Mhz,
			4 - 5Mhz,
			5 - 80 MHz
		Device Allocation: AP"
	DEFVAL	{ 1 }
	::= { wirelessInterface 25 }

wirelessAcceptableAPRSSIThreshold  OBJECT-TYPE
	SYNTAX	   Integer32 (-100..-20)
	MAX-ACCESS read-write
	STATUS	   current
	DESCRIPTION
		"AP RSSI Threshold
		Device Allocation: SM"
	DEFVAL	{ -90 }
	::= { wirelessInterface 26 }

wirelessAcceptableAPCINRThreshold  OBJECT-TYPE
	SYNTAX	   Integer32 (-5..60)
	MAX-ACCESS read-write
	STATUS	   obsolete
	DESCRIPTION
		"AP CINR Threshold
		Device Allocation: SM"
	DEFVAL	{ 0 }
	::= { wirelessInterface 27 }

wirelessInterfaceUnblockUSfreqs	 OBJECT-TYPE
	SYNTAX	   Integer32 (0|1)
	MAX-ACCESS read-write
	STATUS	   obsolete
	DESCRIPTION
		"Block US 5.2 and 5.4 bands
		5.2 and 5.4 bands are blocked until DFS certification is acheived
		Device Allocation: AP, SM"
	::= { wirelessInterface 28 }

wirelessMIREnable  OBJECT-TYPE
	SYNTAX	   Integer32 (0|1)
	MAX-ACCESS read-write
	STATUS	   current
	DESCRIPTION
		"Maximum Information Rate (MIR) Limiting:
			0 - Disable,
			1 - Enable
		Device Allocation: AP"
	DEFVAL	{ 0 }
	::= { wirelessInterface 29 }

wirelessMIRSTAProfileNumber	 OBJECT-TYPE
	SYNTAX	   Integer32 (0..15)
	MAX-ACCESS read-write
	STATUS	   current
	DESCRIPTION
		"Maximum Information Rate (MIR) Limiting Profile Number on SM
		Device Allocation: SM"
	::= { wirelessInterface 30 }

wirelessMIRAPDefaultProfileNumber  OBJECT-TYPE
	SYNTAX	   Integer32 (0..15)
	MAX-ACCESS read-write
	STATUS	   current
	DESCRIPTION
		"Maximum Information Rate (MIR) Limiting Default Profile number on AP
		This Profile Number will be used by AP is SM provides improper profile
		Device Allocation: AP"
	::= { wirelessInterface 31 }

wirelessMIRProfileTable	 OBJECT-TYPE
	SYNTAX SEQUENCE OF WirelessMIRProfileEntry
	MAX-ACCESS not-accessible
	STATUS	   current
	DESCRIPTION
		"Maximum Information Rate (MIR) Limiting profile Table
		Device Allocation: AP"
	::= { wirelessMIRList 1 }

wirelessMIRProfileEntry	 OBJECT-TYPE
	SYNTAX	WirelessMIRProfileEntry
	MAX-ACCESS not-accessible
	STATUS	   current
	DESCRIPTION
		"Maximum Information Rate (MIR) Limiting profile Table Entry
		Device Allocation: AP"
	INDEX	{ wirelessMIRProfileIndex }
	::= { wirelessMIRProfileTable 1 }

WirelessMIRProfileEntry ::= SEQUENCE {
	wirelessMIRProfileIndex
		Integer32,
	wirelessMIRProfileNumber
		Integer32,
	wirelessMIRProfileDescription
		DisplayString,
	wirelessDLMIR
		Integer32,
	wirelessULMIR
		Integer32
}

wirelessMIRProfileIndex	 OBJECT-TYPE
	SYNTAX	   Integer32 (0..16)
	MAX-ACCESS read-write
	STATUS	   current
	DESCRIPTION
		"Maximum Information Rate (MIR) Limiting profile Number
		Device Allocation: AP"
	::= { wirelessMIRProfileEntry 1 }

wirelessMIRProfileNumber  OBJECT-TYPE
	SYNTAX	   Integer32 (0..15)
	MAX-ACCESS read-write
	STATUS	   current
	DESCRIPTION
		"Number of MIR profile
		Device Allocation: AP"
	::= { wirelessMIRProfileEntry 2 }

wirelessMIRProfileDescription  OBJECT-TYPE
	SYNTAX	   DisplayString (SIZE(0|1..128))
	MAX-ACCESS read-write
	STATUS	   current
	DESCRIPTION
		"MIR profile description
		Device Allocation: AP"
	::= { wirelessMIRProfileEntry 3 }


wirelessDLMIR  OBJECT-TYPE
	SYNTAX	   Integer32 (100..1000000)
	MAX-ACCESS read-write
	STATUS	   current
	DESCRIPTION
		"DL MIR in kilobits per second
		Device Allocation: AP"
	::= { wirelessMIRProfileEntry 4 }

wirelessULMIR  OBJECT-TYPE
	SYNTAX	   Integer32 (100..1000000)
	MAX-ACCESS read-write
	STATUS	   current
	DESCRIPTION
		"UL MIR in kilobits per second
		Device Allocation: AP"
	::= { wirelessMIRProfileEntry 5 }

wirelessInterfaceScanFrequencyBandwidth OBJECT-TYPE
	SYNTAX	   Integer32 (1..63)
	MAX-ACCESS read-write
	STATUS	   current
	DESCRIPTION
		"Frequency Bandwidth as bitmask, fields are:
			1 - 20Mhz,
			2 - 40Mhz,
			4 - 10Mhz,
			8 - 5Mhz,
			16 - 80Mhz (802.11ac/ax)
			32 - 160Mhz (Only for 802.11ax)
		Device Allocation: SM"
	DEFVAL	{ 1 }
	::= { wirelessInterface 32 }

wirelessInterfaceGuardInterval OBJECT-TYPE
	SYNTAX Integer32 (1|2|3|4)
	MAX-ACCESS read-write
	STATUS	   current
	DESCRIPTION
		"Guard Interval:
			1 - 0.8 us (long) guard interval,
			2 - 0.4 us (short) guard interval,
			3 - 1.6 us (AX only) guard interval,
			4 - 3.2 us (AX only) guard interval
		Device Allocation: AP"
	DEFVAL	{ 1 }
	::= { wirelessInterface 33 }

wirelessInterfaceiFreqReuseMode OBJECT-TYPE
	SYNTAX Integer32 (0|1|2)
	MAX-ACCESS read-write
	STATUS	   current
	DESCRIPTION
		"Frequency Reuse Mode:
			0 - Off,
			1 - Frequency-Reuse-Front,
			2 - Frequency-Reuse-Back
		Device Allocation: AP"
	DEFVAL	{ 0 }
	::= { wirelessInterface 34 }

wirelessSTAPriority	 OBJECT-TYPE
	SYNTAX	   Integer32 (0|1|2)
	MAX-ACCESS read-write
	STATUS	   current
	DESCRIPTION
		"SM priority value:
			0 - Normal,
			1 - High,
			2 - Low
		Device Allocation: SM"
	DEFVAL	{ 0 }
	::= { wirelessInterface 35 }

wirelessSmoothingBit  OBJECT-TYPE
	SYNTAX	   Integer32 (0|1)
	MAX-ACCESS read-write
	STATUS	   obsolete
	DESCRIPTION
		"Smoothing Bit values:
			0 - Bit is cleared, smoothing is off,
			1 - Bit is set, smoothing is on
		Device Allocation: AP"
	DEFVAL	{ 0 }
	::= { wirelessInterface 36 }

wirelessSecurityMethod	OBJECT-TYPE
	SYNTAX	   Integer32 (0..6)
	MAX-ACCESS read-write
	STATUS	   current
	DESCRIPTION
		"Allowed types of authentications on SM side
		(Preferred AP list is not set)
		Use bitmask to enable pereferred methods, 0 - means enable method:
		set 0-th bit to 0 - Open method (110b)
		set 1-st bit to 0 - WPA2 method (101b)
		set 2-nd bit to 0 - EAP-TTLS method (011b)
		0x00 - All enabled"
	DEFVAL	{ 0 }
	::= { wirelessInterface 37 }

wirelessAcceptableAPSNRThreshold  OBJECT-TYPE
	SYNTAX	   Integer32 (-5..60)
	MAX-ACCESS read-write
	STATUS	   current
	DESCRIPTION
		"AP CINR Threshold
		Device Allocation: SM"
	DEFVAL	{ 0 }
	::= { wirelessInterface 38 }

wirelessMgmtPacketRate	OBJECT-TYPE
	SYNTAX	   Integer32 (0|1)
	MAX-ACCESS read-write
	STATUS	   obsolete
	DESCRIPTION
		"Management rate:
			0 - MCS0
			1 - MCS1
		Device Allocation: AP"
	DEFVAL	{ 1 }
	::= { wirelessInterface 39 }

wirelessStaIsolate	OBJECT-TYPE
	SYNTAX	   Integer32 (0|1)
	MAX-ACCESS read-write
	STATUS	   current
	DESCRIPTION
		"Enables or disables bridging within the AP driver
		between SMs.
			0 - Disabled
			1 - Enabled
		Device Allocation: AP"
	DEFVAL	{ 0 }
	::= { wirelessInterface 40 }

wirelessCcaEnable	OBJECT-TYPE
	SYNTAX		Integer32 (0|1)
	MAX-ACCESS	read-write
	STATUS		current
	DESCRIPTION
		"Clear Channel Assignment:
			0 - Disable
			1 - Enable
		Device Allocation: AP"
	DEFVAL	{ 0 }
	::= { wirelessInterface 41 }

wirelessInterfaceScanFrequencyListTen  OBJECT-TYPE
	SYNTAX	   DisplayString (SIZE(0|1..1500))
	MAX-ACCESS read-write
	STATUS	   current
	DESCRIPTION
		"Scan Frequency List for 10MHz
		Device Allocation: SM"
	::= { wirelessInterface 42 }

wirelessInterfaceScanFrequencyListFive	OBJECT-TYPE
	SYNTAX	   DisplayString (SIZE(0|1..1500))
	MAX-ACCESS read-write
	STATUS	   current
	DESCRIPTION
		"Scan Frequency List for 5MHz
		Device Allocation: SM"
	::= { wirelessInterface 43 }

wirelessMulticastEnhanceMode  OBJECT-TYPE
	SYNTAX	   Integer32 (0|3)
	MAX-ACCESS read-write
	STATUS	   current
	DESCRIPTION
		"Multicast enhancement mode
			0 - Disabled
			3 - IGMP Snooping + MC Passthru
		Device Allocation: AP"
	DEFVAL	{ 0 }
	::= { wirelessInterface 44 }

wirelessTXPowerManualLimit	OBJECT-TYPE
	SYNTAX	   Integer32 (0|1)
	MAX-ACCESS read-write
	STATUS	   current
	DESCRIPTION
		"Allow user to limit MAX output TX Power
		Device Allocation: SM"
	DEFVAL	{ 0 }
	::= { wirelessInterface 48 }

wirelessRateMaxMCS OBJECT-TYPE
	SYNTAX	   Integer32 (1..255)
	MAX-ACCESS not-accessible
	STATUS	   obsolete
	DESCRIPTION
		"Allow user to set MAX TX rate
		Not allowed for SNMP processing
		Device Allocation: AP, SM"
	::= { wirelessInterface 49 }

wirelessSMWifiDistance	OBJECT-TYPE
	SYNTAX	   Integer32 (1..52)
	MAX-ACCESS read-write
	STATUS	   current
	DESCRIPTION
		"Distance to AP for SM in Standard Wi-Fi mode
		wirelessCellSizeUnitdefines the unit type:
			1 - Miles
			2 - Kilometers
		Device Allocation: SM"
	DEFVAL	{ 1 }
	::= { wirelessInterface 50 }

wirelessInterfaceProtocolMode  OBJECT-TYPE
	SYNTAX	   Integer32 (1..5)
	MAX-ACCESS read-write
	STATUS	   current
	DESCRIPTION
		"Protocol Module Mode:
		 1 - TDD
		 2 - AP/SM WiFi
		 3 - PTP.LL
		 4 - TDD PTP
		 5 - WLR
		Device Allocation: AP/SM"
	DEFVAL  { 1 }
	::= { wirelessInterface 51 }

wirelessClientBridgeMode OBJECT-TYPE
	SYNTAX Integer32 (0|1)
	MAX-ACCESS read-write
	STATUS     current
	DESCRIPTION
		"Enables ARPNAT feature, translates ARP requests from Ethernet side of SM to Wireless and vice-versa:
			0 - Disabled
			1 - Enabled
		Device Allocation: SM"
	DEFVAL  { 0 }
	::= { wirelessInterface 52 }

forceMcastBcast4Addr  OBJECT-TYPE
	SYNTAX	   Integer32 (0|1)
	MAX-ACCESS read-write
	STATUS	   current
	DESCRIPTION
		"1 - TRUE
		0 - FALSE"
	DEFVAL  { 1 }
	::= { wirelessInterface 53 }

wirelessInterfaceCipher	 OBJECT-TYPE
	SYNTAX	   Integer32 (1|2)
	MAX-ACCESS read-write
	STATUS	   current
	DESCRIPTION
		"Wireless authentication cipher type:
			1 - AES-128 (CCMP (128 bits)),
			2 - AES-256 (CCMP-256 (256 bits))
		Device Allocation: AP"
	DEFVAL	{ 2 }
	::= { wirelessInterface 54 }

wirelessInterfaceRateMinMCS	 OBJECT-TYPE
	SYNTAX	   Integer32 (1..7|9..15|21..29|31..39)
	MAX-ACCESS read-write
	STATUS	   current
	DESCRIPTION
		"Minimum locked MCS rate.
		Default allocation: AP, SM."
	::= { wirelessInterface 55 }

wirelessInterfaceRateMaxMCS  OBJECT-TYPE
	SYNTAX     Integer32 (1..7|9..15|21..29|31..39)
	MAX-ACCESS read-write
	STATUS     current
	DESCRIPTION
		"Maximum locked MCS rate.
		For hw 802.11n:
		1..7 for SS and 9..15 for DS MCS is used.
		For hw 802.11ac:
		Next formula is used
		NSS (For SS - 1, For DS - 2 ) * 10 + MCS

		20 for 'SS MCS 0 - BPSK 1/2',
		21 for 'SS MCS 1 - QPSK 1/2',
		22 for 'SS MCS 2 - QPSK 3/4',
		23 for 'SS MCS 3 - 16-QAM 1/2',
		24 for 'SS MCS 4 - 16-QAM 3/4',
		25 for 'SS MCS 5 - 64-QAM 2/3',
		26 for 'SS MCS 6 - 64-QAM 3/4',
		27 for 'SS MCS 7 - 64-QAM 5/6',
		28 for 'SS MCS 8 - 256-QAM 3/4',
		29 for 'SS MCS 9 - 256-QAM 5/6',

		30 for 'DS MCS 0 - BPSK 1/2',
		31 for 'DS MCS 1 - QPSK 1/2',
		32 for 'DS MCS 2 - QPSK 3/4',
		33 for 'DS MCS 3 - 16-QAM 1/2',
		34 for 'DS MCS 4 - 16-QAM 3/4',
		35 for 'DS MCS 5 - 64-QAM 2/3',
		36 for 'DS MCS 6 - 64-QAM 3/4',
		37 for 'DS MCS 7 - 64-QAM 5/6',
		38 for 'DS MCS 8 - 256-QAM 3/4',
		39 for 'DS MCS 9 - 256-QAM 5/6',

		For hw 802.11ax:

		192 for 'SS MCS 0 - BPSK 1/2',
		193 for 'SS MCS 1 - QPSK 1/2',
		194 for 'SS MCS 2 - QPSK 3/4',
		195 for 'SS MCS 3 - 16-QAM 1/2',
		196 for 'SS MCS 4 - 16-QAM 3/4',
		197 for 'SS MCS 5 - 64-QAM 2/3',
		198 for 'SS MCS 6 - 64-QAM 3/4',
		199 for 'SS MCS 7 - 64-QAM 5/6',
		200 for 'SS MCS 8 - 256-QAM 3/4',
		201 for 'SS MCS 9 - 256-QAM 5/6',
		202 for 'SS MCS 10- 1024-QAM 3/4',
		203 for 'SS MCS 11- 1024-QAM 5/6',
		204 for 'SS MCS 12- 4096-QAM 3/4',
		205 for 'SS MCS 13- 4096-QAM 5/6',

		208 for 'DS MCS 0 - BPSK 1/2',
		209 for 'DS MCS 1 - QPSK 1/2',
		210 for 'DS MCS 2 - QPSK 3/4',
		211 for 'DS MCS 3 - 16-QAM 1/2',
		212 for 'DS MCS 4 - 16-QAM 3/4',
		213 for 'DS MCS 5 - 64-QAM 2/3',
		214 for 'DS MCS 6 - 64-QAM 3/4',
		215 for 'DS MCS 7 - 64-QAM 5/6',
		216 for 'DS MCS 8 - 256-QAM 3/4',
		217 for 'DS MCS 9 - 256-QAM 5/6',
		218 for 'DS MCS 10- 1024-QAM 3/4',
		219 for 'DS MCS 11- 1024-QAM 5/6',
		220 for 'DS MCS 12- 4096-QAM 3/4',
		221 for 'DS MCS 13- 4096-QAM 5/6',

		Default allocation: AP, SM."
	::= { wirelessInterface 56 }

wirelessMulticastIgmpFastLeave  OBJECT-TYPE
	SYNTAX     Integer32 (0|1)
	MAX-ACCESS read-write
	STATUS     current
	DESCRIPTION
		"Multicast enhancement mode
		0 - IGMP Fast Leave OFF
		1 - IGMP Fast Leave ON
		Device Allocation: AP"
	DEFVAL  { 0 }
	::= { wirelessInterface 57 }

wirelessInterfaceTDDFrameSize  OBJECT-TYPE
	SYNTAX     Integer32 (2500|5000)
	MAX-ACCESS read-write
	STATUS     current
	DESCRIPTION
		"TDD Frame Duration in microseconds
			2500 - 2.5 ms
			5000 - 5 ms
		Device Allocation: AP"
	DEFVAL  { 5000 }
	::= { wirelessInterface 58 }

wirelessInterfaceColocState  OBJECT-TYPE
	SYNTAX     Integer32 (0|1)
	MAX-ACCESS read-write
	STATUS     current
	DESCRIPTION
		"Co-location state
			0 - disabled
			1 - FSK co-location
		Device Allocation: AP"
	DEFVAL  { 0 }
	::= { wirelessInterface 59 }

wirelessInterfaceColocSystemSyncSrc  OBJECT-TYPE
	SYNTAX     Integer32 (1|2|4|5)
	MAX-ACCESS read-write
	STATUS     current
	DESCRIPTION
		"Co-location state
			1 - GPS,
			2 - CMM4,
			4 - CMM3,
			5 - CMM5 (802.11ac only)
		Device Allocation: AP"
	DEFVAL  { 2 }
	::= { wirelessInterface 60 }

wirelessAPWifiWLANmode  OBJECT-TYPE
	SYNTAX     Integer32 (0|1)
	MAX-ACCESS read-write
	STATUS     current
	DESCRIPTION
		"AP Wi-Fi WLAN mode (short, 1000m operational distance)
			0 - Disabled,
			1 - Enabled
		Device Allocation: AP"
	DEFVAL  { 0 }
	::= { wirelessInterface 61 }

apWiFiDLCTSMode  OBJECT-TYPE
	SYNTAX     Integer32 (0|1)
	MAX-ACCESS read-write
	STATUS     current
	DESCRIPTION
		"Force AP WiFi to enable Self CTS
			0 - Disabled,
			1 - Enabled
		Device Allocation: AP"
	DEFVAL  { 1 }
	::= { wirelessInterface 62 }

apWiFiULCTSRTSMode  OBJECT-TYPE
	SYNTAX     Integer32 (0|1)
	MAX-ACCESS read-write
	STATUS     current
	DESCRIPTION
		"Force AP WiFi to add ERP IE to the Beacon
			0 - Disabled,
			1 - Enabled
		Device Allocation: AP"
	DEFVAL  { 1 }
	::= { wirelessInterface 63 }

apWiFiRTSThreshold  OBJECT-TYPE
	SYNTAX     Integer32 (1..2346)
	MAX-ACCESS read-write
	STATUS     current
	DESCRIPTION
		"Wi-Fi interface RTS Threshold
		Device Allocation: AP, SM"
	DEFVAL  { 2346 }
	::= { wirelessInterface 64 }

apWiFiCompWDSTrBridge  OBJECT-TYPE
	SYNTAX     Integer32 (0|1)
	MAX-ACCESS read-write
	STATUS     current
	DESCRIPTION
		"AP Wi-Fi WDS Transparent bridge mode
		Compatibility mode for Ubiquity WDS Transparent bridge
		and Mikrotik station wds
			0 - Disabled,
			1 - Enabled
		Device Allocation: AP"
	DEFVAL  { 1 }
	::= { wirelessInterface 65 }

wirelessFreqShift  OBJECT-TYPE
	SYNTAX	   Integer32 (0..50)
	MAX-ACCESS read-write
	STATUS	   current
	DESCRIPTION
		"Freq shift in 0.1 Mhz units:
		Range: 0..50 (0..5Mhz)
		Device Allocation: AP, STA"
	DEFVAL	{ 0 }
	::= { wirelessInterface 66 }

wirelessFBCompatibility  OBJECT-TYPE
	SYNTAX     Integer32 (0|1)
	MAX-ACCESS read-write
	STATUS     current
	DESCRIPTION
		"for  802.11n-based AP enable Forward Compatability, allow connect 802.11ac-based SMs
		 for 802.11ac-based AP enable Backward Compatibility, allow connect 802.11n-based SMs
			0 - Disabled
			1 - Enabled
		Device Allocation: AP"
	DEFVAL  { 0 }
	::= { wirelessInterface 67 }

wirelessMACFilter  OBJECT-TYPE
	SYNTAX     Integer32 (0|1)
	MAX-ACCESS read-write
	STATUS     current
	DESCRIPTION
		"Enable/Disable MAC list filter
			0 - Disabled,
			1 - Enabled
		Device Allocation: AP"
	DEFVAL  { 0 }
	::= { wirelessInterface 70 }

wirelessMACFilterPolicy  OBJECT-TYPE
	SYNTAX     Integer32 (1|2)
	MAX-ACCESS read-write
	STATUS     current
	DESCRIPTION
		"Permit/Prevent policy for MAC list
			1 - Prevent
			2 - Permit
		Device Allocation: AP"
	DEFVAL  { 1 }
	::= { wirelessInterface 71 }

wirelessMACFilterTable	 OBJECT-TYPE
	SYNTAX SEQUENCE OF WirelessMACFilterEntry
	MAX-ACCESS not-accessible
	STATUS	   current
	DESCRIPTION
		"Table for MAC filter list
		Device Allocation: AP"
	::= { wirelessInterface 72 }

wirelessInterfaceMgmtRadioBoarddata  OBJECT-TYPE
	SYNTAX     Integer32 (0|1)
	MAX-ACCESS read-write
	STATUS     current
	DESCRIPTION
		"Switch management radio between 2.4G and 5G
		This Prameters is applicable only for F220/F300 HW.
		0 - No change (5G),
		1 - Enabled 2.4G
		Device Allocation: AP"
	DEFVAL  { 0 }
	::= { wirelessInterface 73 }

wirelessPMPWDSUnknownMACFlood	OBJECT-TYPE
	SYNTAX     Integer32 (0|1)
	MAX-ACCESS read-write
	STATUS	   current
	DESCRIPTION
		"Permit/prevent flooding of
		unicast packets with unknown
		MAC address
			0 - prevent
			1 - permit
		Device Allocation: AP"
	::= { wirelessInterface 74 }

wirelessInterfaceScanFrequencyListEighty  OBJECT-TYPE
	SYNTAX	   DisplayString (SIZE(0|1..1500))
	MAX-ACCESS read-write
	STATUS	   current
	DESCRIPTION
		"Scan Frequency List for 80 MHz
		Device Allocation: SM"
	::= { wirelessInterface 80 }

wirelessInterfaceVHTMCS	 OBJECT-TYPE
	SYNTAX	   Integer32 (0..9)
	MAX-ACCESS read-write
	STATUS	   current
	DESCRIPTION
		"Fixed rate:
			0 - VHT MCS0
			1 - VHT MCS1
			2 - VHT MCS2
			3 - VHT MCS3
			4 - VHT MCS4
			5 - VHT MCS5
			6 - VHT MCS6
			7 - VHT MCS7
			8 - VHT MCS8
			9 - VHT MCS9
		Device Allocation: AP, SM"
	DEFVAL	{ 9 }
	::= { wirelessInterface 81 }

wirelessInterfaceNSS	 OBJECT-TYPE
	SYNTAX	   Integer32 (1..2)
	MAX-ACCESS read-write
	STATUS	   current
	DESCRIPTION
		"Number of spatial streams
		1 - single    spatial stream
		2 - double    spatial stream
		Device Allocation: AP, SM"
	DEFVAL	{ 2 }
	::= { wirelessInterface 82 }

mikrotikFreqShift	 OBJECT-TYPE
	SYNTAX	   Integer32 (-50..50)
	MAX-ACCESS read-write
	STATUS	   current
	DESCRIPTION
		"Frequency tuning for Mikrotik temperature deviation issue, 100 KHz step"
	DEFVAL	{ 0 }
	::= { wirelessInterface 83 }

cambiumKeepAliveIface1	OBJECT IDENTIFIER ::= { wirelessInterface 84 }

wirelessInterface1KeepAliveEnable	 OBJECT-TYPE
	SYNTAX	   Integer32 (0|1)
	MAX-ACCESS read-write
	STATUS	   current
	DESCRIPTION
		"Enables Cambium KeepAlive feature for TDD PTP driver mode"
	DEFVAL	{ 0 }
	::= { cambiumKeepAliveIface1 1 }

wirelessInterface1KeepAliveEPTPEnable	 OBJECT-TYPE
	SYNTAX	   Integer32 (0|1)
	MAX-ACCESS read-write
	STATUS	   current
	DESCRIPTION
		"Enables Cambium KeepAlive feature for ePTP driver mode"
	DEFVAL	{ 1 }
	::= { cambiumKeepAliveIface1 2 }

wirelessInterface1KeepAlivePMPEnable	 OBJECT-TYPE
	SYNTAX	   Integer32 (0|1)
	MAX-ACCESS read-write
	STATUS	   current
	DESCRIPTION
		"Enables Cambium KeepAlive feature for TDD PMP driver mode"
	DEFVAL	{ 1 }
	::= { cambiumKeepAliveIface1 3 }

wirelessInterface1KeepAliveWLREnable	 OBJECT-TYPE
	SYNTAX	   Integer32 (0|1)
	MAX-ACCESS read-write
	STATUS	   current
	DESCRIPTION
		"Enables Cambium KeepAlive feature for TDD PMP driver mode"
	DEFVAL	{ 1 }
	::= { cambiumKeepAliveIface1 4 }

wirelessInterfaceSTAMaxDLMCSLimit  OBJECT-TYPE
	SYNTAX     Integer32 (0..9|16..25|255)
	MAX-ACCESS read-write
	STATUS     current
	DESCRIPTION
		"Radio max DL MCS limit:
			0 - MCS 0 (802.11n) or MCS 0 SS (802.11ac)
			1 - MCS 1 (802.11n) or MCS 1 SS (802.11ac)
			2 - MCS 2 (802.11n) or MCS 2 SS (802.11ac)
			3 - MCS 3 (802.11n) or MCS 3 SS (802.11ac)
			4 - MCS 4 (802.11n) or MCS 4 SS (802.11ac)
			5 - MCS 5 (802.11n) or MCS 5 SS (802.11ac)
			6 - MCS 6 (802.11n) or MCS 6 SS (802.11ac)
			7 - MCS 7 (802.11n) or MCS 7 SS (802.11ac)
			8 - MCS 8 SS (802.11ac)
			9 - MCS 9 SS (802.11ac)
			16 - MCS 8 (802.11n) or MCS 0 DS (802.11ac)
			17 - MCS 9 (802.11n) or MCS 1 DS (802.11ac)
			18 - MCS 10 (802.11n) or MCS 2 DS (802.11ac)
			19 - MCS 11 (802.11n) or MCS 3 DS (802.11ac)
			20 - MCS 12 (802.11n) or MCS 4 DS (802.11ac)
			21 - MCS 13 (802.11n) or MCS 5 DS (802.11ac)
			22 - MCS 14 (802.11n) or MCS 6 DS (802.11ac)
			23 - MCS 15 (802.11n) or MCS 7 DS (802.11ac)
			24 - MCS 8 DS (802.11ac)
			25 - MCS 9 DS (802.11ac)
			255 - Use AP's config
		Device Allocation: SM"
	DEFVAL	{ 255 }
	::= { wirelessInterface 85 }

wirelessInterfaceScanFrequencyList160M  OBJECT-TYPE
	SYNTAX	   DisplayString (SIZE(0|1..1500))
	MAX-ACCESS read-write
	STATUS	   current
	DESCRIPTION
		"Scan Frequency List for 160 MHz
		Device Allocation: SM"
	::= { wirelessInterface 86 }

wirelessInterfaceSuRxBfOff OBJECT-TYPE
	SYNTAX     Integer32(0|1)
	MAX-ACCESS read-write
	STATUS     current
	DESCRIPTION
		"Control of SM SU beamforming in transmit mode:
			0 - SU beamforming is On
			1 - SU beamforming is Off
		Device Allocation: SM"
	DEFVAL { 0 }
	::= { wirelessInterface 87 }

wirelessInterface2HTMode  OBJECT-TYPE
	SYNTAX     Integer32 (1..5)
	MAX-ACCESS read-write
	STATUS     current
	DESCRIPTION
		"Second Radio Frequency Bandwidth
			1 - 20Mhz,
			2 - 40Mhz,
			3 - 10Mhz,
			4 - 5MHz,
			5 - 80MHz
		Device Allocation: AP"
	DEFVAL  { 1 }
	::= { wirelessInterface2 5 }

wirelessInterface2TXPower  OBJECT-TYPE
	SYNTAX     Integer32 (-24..30)
	MAX-ACCESS read-write
	STATUS     current
	DESCRIPTION
		"Second Radio TX Power (Board Output Conducted)
		In the SM mode this parameter can be changed
		only if wirelessTXPowerManualLimit2 is 1;
		Device Allocation: AP, SM"
	DEFVAL  { 7 }
	::= { wirelessInterface2 6 }

wirelessInterface2ScanFrequencyListTwenty  OBJECT-TYPE
	SYNTAX     DisplayString (SIZE(0|1..1500))
	MAX-ACCESS read-write
	STATUS     current
	DESCRIPTION
		"Second Radio Scan Frequency List for 20 MHz
		Device Allocation: SM"
	::= { wirelessInterface2 16 }

wirelessInterface2ScanFrequencyListForty  OBJECT-TYPE
	SYNTAX     DisplayString (SIZE(0|1..1500))
	MAX-ACCESS read-write
	STATUS     current
	DESCRIPTION
		"Second Radio Scan Frequency List for 40 MHz
		Device Allocation: SM"
	::= { wirelessInterface2 17 }

centerFrequency2  OBJECT-TYPE
	SYNTAX     Integer32 (0|2355..7200)
	MAX-ACCESS read-write
	STATUS     current
	DESCRIPTION
		"Second Radio Per freq band: 5725 GHz for 5G SKU, 2355 for 2.4G SKU
		Device Allocation: AP"
	::= { wirelessInterface2 18 }

dfsAlternative1CenterFrequency2  OBJECT-TYPE
	SYNTAX	   Integer32 (0|2355..7200)
	MAX-ACCESS read-write
	STATUS	   current
	DESCRIPTION
		"Second Radio Per freq band
		Device Allocation: AP"
	::= { wirelessInterface2 19 }

dfsAlternative2CenterFrequency2  OBJECT-TYPE
	SYNTAX	   Integer32 (0|2355..7200)
	MAX-ACCESS read-write
	STATUS	   current
	DESCRIPTION
		"Second Radio Per freq band
		Device Allocation: AP"
	::= { wirelessInterface2 20 }

dfsAlternative1Bandwidth2  OBJECT-TYPE
	SYNTAX	   Integer32 (1..5)
	MAX-ACCESS read-write
	STATUS	   current
	DESCRIPTION
		"Second Radio Frequency Bandwidth
			1 - 20Mhz,
			2 - 40Mhz,
			3 - 10Mhz,
			4 - 5Mhz,
			5 - 80MHz
		Device Allocation: AP"
	DEFVAL	{ 1 }
	::= { wirelessInterface2 24 }

dfsAlternative2Bandwidth2  OBJECT-TYPE
	SYNTAX	   Integer32 (1..5)
	MAX-ACCESS read-write
	STATUS	   current
	DESCRIPTION
		"Second Radio Frequency Bandwidth
			1 - 20Mhz,
			2 - 40Mhz,
			3 - 10Mhz,
			4 - 5Mhz,
			5 - 80MHz
		Device Allocation: AP"
	DEFVAL	{ 1 }
	::= { wirelessInterface2 25 }

wirelessInterface2ScanFrequencyBandwidth OBJECT-TYPE
	SYNTAX     Integer32 (1..31)
	MAX-ACCESS read-write
	STATUS     current
	DESCRIPTION
		"Second Radio Frequency Bandwidth as bitmask, fields are:
			1 - 20Mhz,
			2 - 40Mhz,
			4 - 10Mhz,
			8 - 5Mhz,
			16 - 80Mhz
		Device Allocation: SM"
	DEFVAL  { 1 }
	::= { wirelessInterface2 32 }

wirelessInterface2ScanFrequencyListFive  OBJECT-TYPE
	SYNTAX     DisplayString (SIZE(0|1..1500))
	MAX-ACCESS read-write
	STATUS     current
	DESCRIPTION
		"Second Radio Scan Frequency List for 5 MHz
		Device Allocation: SM"
	::= { wirelessInterface2 42 }

wirelessInterface2ScanFrequencyListTen  OBJECT-TYPE
	SYNTAX     DisplayString (SIZE(0|1..1500))
	MAX-ACCESS read-write
	STATUS     current
	DESCRIPTION
		"Second Radio Scan Frequency List for 10 MHz
		Device Allocation: SM"
	::= { wirelessInterface2 43 }

wirelessTXPowerManualLimit2	OBJECT-TYPE
	SYNTAX     Integer32 (0|1)
	MAX-ACCESS read-write
	STATUS     current
	DESCRIPTION
		"Allow user to limit MAX output TX Power
		Device Allocation: SM"
	DEFVAL	{ 0 }
	::= { wirelessInterface2 48 }

wirelessInterface2RateMinMCS      OBJECT-TYPE
	SYNTAX     Integer32 (21..29|31..39)
	MAX-ACCESS read-write
	STATUS     current
	DESCRIPTION
		"Second Radio Minimum locked MCS rate.
		Default allocation: AP, SM."
	DEFVAL  { 21 }
	::= { wirelessInterface2 55 }

wirelessInterface2RateMaxMCS  OBJECT-TYPE
	SYNTAX     Integer32 (21..29|31..39)
	MAX-ACCESS read-write
	STATUS     current
	DESCRIPTION
		"Second Radio Maximum locked MCS rate.
		For hw 802.11n:
		1..7 for SS and 9..15 for DS MCS is used.
		For hw 802.11ac:
		Next formula is used
		NSS (For SS - 1, For DS - 2 ) * 10 + MCS

		20 for 'SS MCS 0 - BPSK 1/2',
		21 for 'SS MCS 1 - QPSK 1/2',
		22 for 'SS MCS 2 - QPSK 3/4',
		23 for 'SS MCS 3 - 16-QAM 1/2',
		24 for 'SS MCS 4 - 16-QAM 3/4',
		25 for 'SS MCS 5 - 64-QAM 2/3',
		26 for 'SS MCS 6 - 64-QAM 3/4',
		27 for 'SS MCS 7 - 64-QAM 5/6',
		28 for 'SS MCS 8 - 256-QAM 3/4',
		29 for 'SS MCS 9 - 256-QAM 5/6',

		30 for 'DS MCS 0 - BPSK 1/2',
		31 for 'DS MCS 1 - QPSK 1/2',
		32 for 'DS MCS 2 - QPSK 3/4',
		33 for 'DS MCS 3 - 16-QAM 1/2',
		34 for 'DS MCS 4 - 16-QAM 3/4',
		35 for 'DS MCS 5 - 64-QAM 2/3',
		36 for 'DS MCS 6 - 64-QAM 3/4',
		37 for 'DS MCS 7 - 64-QAM 5/6',
		38 for 'DS MCS 8 - 256-QAM 3/4',
		39 for 'DS MCS 9 - 256-QAM 5/6',

		For hw 802.11ax:

		192 for 'SS MCS 0 - BPSK 1/2',
		193 for 'SS MCS 1 - QPSK 1/2',
		194 for 'SS MCS 2 - QPSK 3/4',
		195 for 'SS MCS 3 - 16-QAM 1/2',
		196 for 'SS MCS 4 - 16-QAM 3/4',
		197 for 'SS MCS 5 - 64-QAM 2/3',
		198 for 'SS MCS 6 - 64-QAM 3/4',
		199 for 'SS MCS 7 - 64-QAM 5/6',
		200 for 'SS MCS 8 - 256-QAM 3/4',
		201 for 'SS MCS 9 - 256-QAM 5/6',
		202 for 'SS MCS 10- 1024-QAM 3/4',
		203 for 'SS MCS 11- 1024-QAM 5/6',
		204 for 'SS MCS 12- 4096-QAM 3/4',
		205 for 'SS MCS 13- 4096-QAM 5/6',

		208 for 'DS MCS 0 - BPSK 1/2',
		209 for 'DS MCS 1 - QPSK 1/2',
		210 for 'DS MCS 2 - QPSK 3/4',
		211 for 'DS MCS 3 - 16-QAM 1/2',
		212 for 'DS MCS 4 - 16-QAM 3/4',
		213 for 'DS MCS 5 - 64-QAM 2/3',
		214 for 'DS MCS 6 - 64-QAM 3/4',
		215 for 'DS MCS 7 - 64-QAM 5/6',
		216 for 'DS MCS 8 - 256-QAM 3/4',
		217 for 'DS MCS 9 - 256-QAM 5/6',
		218 for 'DS MCS 10- 1024-QAM 3/4',
		219 for 'DS MCS 11- 1024-QAM 5/6',
		220 for 'DS MCS 12- 4096-QAM 3/4',
		221 for 'DS MCS 13- 4096-QAM 5/6',

		Default allocation: AP, SM."
	DEFVAL  { 39 }
	::= { wirelessInterface2 56 }

wirelessInterface2ScanFrequencyListEighty  OBJECT-TYPE
	SYNTAX     DisplayString (SIZE(0|1..1500))
	MAX-ACCESS read-write
	STATUS     current
	DESCRIPTION
		"Second Radio Scan Frequency List for 80 MHz
		Device Allocation: SM"
	::= { wirelessInterface2 80 }

cambiumKeepAliveIface2		OBJECT IDENTIFIER ::= { wirelessInterface2 84 }

wirelessInterface2KeepAliveEnable	 OBJECT-TYPE
	SYNTAX	   Integer32 (0|1)
	MAX-ACCESS read-write
	STATUS	   current
	DESCRIPTION
		"Second Radio Enables Cambium KeepAlive feature for TDD PTP driver mode"
	DEFVAL	{ 0 }
	::= { cambiumKeepAliveIface2 1 }

wirelessInterface2KeepAliveEPTPEnable	 OBJECT-TYPE
	SYNTAX	   Integer32 (0|1)
	MAX-ACCESS read-write
	STATUS	   current
	DESCRIPTION
		"Second Radio Enables Cambium KeepAlive feature for ePTP driver mode"
	DEFVAL	{ 0 }
	::= { cambiumKeepAliveIface2 2 }

wirelessInterface2STAMaxDLMCSLimit  OBJECT-TYPE
	SYNTAX     Integer32 (0..9|16..25|255)
	MAX-ACCESS read-write
	STATUS     current
	DESCRIPTION
		"Second Radio max DL MCS limit:
			0 - MCS 0 SS
			1 - MCS 1 SS
			2 - MCS 2 SS
			3 - MCS 3 SS
			4 - MCS 4 SS
			5 - MCS 5 SS
			6 - MCS 6 SS
			7 - MCS 7 SS
			8 - MCS 8 SS
			9 - MCS 9 SS
			16 - MCS 0 DS
			17 - MCS 1 DS
			18 - MCS 2 DS
			19 - MCS 3 DS
			20 - MCS 4 DS
			21 - MCS 5 DS
			22 - MCS 6 DS
			23 - MCS 7 DS
			24 - MCS 8 DS
			25 - MCS 9 DS
			255 - Use AP's config
		Device Allocation: SM"
	DEFVAL	{ 255 }
	::= { wirelessInterface2 85 }

wirelessInterface2SuRxBfOff OBJECT-TYPE
	SYNTAX     Integer32(0|1)
	MAX-ACCESS read-write
	STATUS     current
	DESCRIPTION
		"Control of SM SU beamforming in transmit mode:
			0 - SU beamforming is On
			1 - SU beamforming is Off
		Device Allocation: SM"
	DEFVAL { 0 }
	::= { wirelessInterface2 87 }

wirelessMACFilterEntry	 OBJECT-TYPE
	SYNTAX	WirelessMACFilterEntry
	MAX-ACCESS not-accessible
	STATUS	   current
	DESCRIPTION
		"L2 ACL Table Entry
		Device Allocation: AP"
	INDEX	{ wirelessMACFilterIndex }
	::= { wirelessMACFilterTable 1 }

WirelessMACFilterEntry ::= SEQUENCE {
	wirelessMACFilterIndex
		Integer32,
	wirelessFilterMAC
		DisplayString,
	wirelessFilterInfo
		DisplayString
}

wirelessMACFilterIndex  OBJECT-TYPE
	SYNTAX	   Integer32 (0..128)
	MAX-ACCESS read-write
	STATUS	   current
	DESCRIPTION
		"MAC filter list table Index(equal max STA)
		Table Entry is cleared if Index is set to zero
		Device Allocation: AP"
	::= { wirelessMACFilterEntry 1 }

wirelessFilterMAC	 OBJECT-TYPE
	SYNTAX	   DisplayString (SIZE(0|1..128))
	MAX-ACCESS read-write
	STATUS	   current
	DESCRIPTION
		"MAC of SM for filter table
		Device Allocation: AP"
	::= { wirelessMACFilterEntry 2 }

wirelessFilterInfo	 OBJECT-TYPE
	SYNTAX	   DisplayString (SIZE(0|1..128))
	MAX-ACCESS read-write
	STATUS	   current
	DESCRIPTION
		"Description for MAC in the filter table
		Device Allocation: AP"
	::= { wirelessMACFilterEntry 3 }

l2FirewallEnable  OBJECT-TYPE
	SYNTAX	   Integer32 (0|1)
	MAX-ACCESS read-write
	STATUS	   current
	DESCRIPTION
		"L2 ACL Status Flag:
			0 - Disable,
			1 - Enable.
		Device Allocation: AP, SM"
	::= { l2Firewall 1 }

l2FirewallTable	 OBJECT-TYPE
	SYNTAX SEQUENCE OF L2FirewallEntry
	MAX-ACCESS not-accessible
	STATUS	   current
	DESCRIPTION
		"Table for L2 ACL
		Device Allocation: AP, SM"
	::= { l2Firewall 2 }

l2FirewallEntry	 OBJECT-TYPE
	SYNTAX	L2FirewallEntry
	MAX-ACCESS not-accessible
	STATUS	   current
	DESCRIPTION
		"L2 ACL Table Entry
		Device Allocation: AP, SM"
	INDEX	{ l2FirewallEntryIndex }
	::= { l2FirewallTable 1 }

L2FirewallEntry ::= SEQUENCE {
	l2FirewallEntryIndex
		Integer32,
	l2FirewallEntryName
		DisplayString,
	l2FirewallEntryAction
		Integer32,
	l2FirewallEntryInterface
		Integer32,
	l2FirewallEntryLog
		Integer32,
	l2FirewallEntryEtherType
		Integer32,
	l2FirewallEntryVlanID
		Integer32,
	l2FirewallEntrySrcMAC
		DisplayString,
	l2FirewallEntrySrcMask
		DisplayString,
	l2FirewallEntryDstMAC
		DisplayString,
	l2FirewallEntryDstMask
		DisplayString
}

l2FirewallEntryIndex  OBJECT-TYPE
	SYNTAX	   Integer32 (0..16)
	MAX-ACCESS read-write
	STATUS	   current
	DESCRIPTION
		"L2 Firewall Table Index
		Table Entry is cleared if Index is set to zero
		Device Allocation: AP, SM"
	::= { l2FirewallEntry 1 }

l2FirewallEntryName	 OBJECT-TYPE
	SYNTAX	   DisplayString (SIZE(0|1..128))
	MAX-ACCESS read-write
	STATUS	   current
	DESCRIPTION
		"L2 ACL Rule Name.
		Device Allocation: AP, SM"
	::= { l2FirewallEntry 2 }

l2FirewallEntryAction  OBJECT-TYPE
	SYNTAX	   Integer32 (0|1)
	MAX-ACCESS read-write
	STATUS	   current
	DESCRIPTION
		"Action:
			0 - Reject,
			1 - Permit.
		Device Allocation: AP, SM"
	::= { l2FirewallEntry 3 }

l2FirewallEntryInterface  OBJECT-TYPE
	SYNTAX	   Integer32 (0|1|2)
	MAX-ACCESS read-write
	STATUS	   current
	DESCRIPTION
		"Interface:
			1 - WAN,
			2 - LAN.
		Device Allocation: AP, SM"
	::= { l2FirewallEntry 4 }

l2FirewallEntryLog	OBJECT-TYPE
	SYNTAX	   Integer32 (0|1)
	MAX-ACCESS read-write
	STATUS	   current
	DESCRIPTION
		"Log:
			1 - On,
			0 - Off.
		Device Allocation: AP, SM"
	::= { l2FirewallEntry 5 }

l2FirewallEntryEtherType  OBJECT-TYPE
	SYNTAX	   Integer32 (0..65535)
	MAX-ACCESS read-write
	STATUS	   current
	DESCRIPTION
		"L2 ACL Ethernet type: 0000-ffff
		Device Allocation: AP, SM"
	::= { l2FirewallEntry 6 }

l2FirewallEntryVlanID  OBJECT-TYPE
	SYNTAX	   Integer32 (0|1..4094)
	MAX-ACCESS read-write
	STATUS	   current
	DESCRIPTION
		"L2 ACL Vlan ID
		Device Allocation: AP, SM"
	::= { l2FirewallEntry 7 }

l2FirewallEntrySrcMAC  OBJECT-TYPE
	SYNTAX	   DisplayString (SIZE(0|11..17))
	MAX-ACCESS read-write
	STATUS	   current
	DESCRIPTION
		"L2 ACL Source MAC Address
		Device Allocation: AP, SM"
	::= { l2FirewallEntry 8 }

l2FirewallEntrySrcMask	OBJECT-TYPE
	SYNTAX	   DisplayString (SIZE(0|11..17))
	MAX-ACCESS read-write
	STATUS	   current
	DESCRIPTION
		"L2 ACL Source MAC Address Mask
		Device Allocation: AP, SM"
	::= { l2FirewallEntry 9 }

l2FirewallEntryDstMAC  OBJECT-TYPE
	SYNTAX	   DisplayString (SIZE(0|11..17))
	MAX-ACCESS read-write
	STATUS	   current
	DESCRIPTION
		"L2 ACL Destination MAC Address
		Device Allocation: AP, SM"
	::= { l2FirewallEntry 10 }

l2FirewallEntryDstMask	OBJECT-TYPE
	SYNTAX	   DisplayString (SIZE(0|11..17))
	MAX-ACCESS read-write
	STATUS	   current
	DESCRIPTION
		"L2 ACL Destination MAC Address Mask
		Device Allocation: AP, SM"
	::= { l2FirewallEntry 11 }

l2WanRemoteAccess  OBJECT-TYPE
	SYNTAX	   Integer32 (0|1)
	MAX-ACCESS read-write
	STATUS	   current
	DESCRIPTION
		"Remote Access To AP Through Wan:
			0 - Decline,
			1 - Allow
		Device Allocation: AP, SM"
	DEFVAL	{ 0 }
	::= { l2Firewall 3 }

l2SnmpLanRemoteAccess  OBJECT-TYPE
	SYNTAX	   Integer32 (0|1)
	MAX-ACCESS read-write
	STATUS	   current
	DESCRIPTION
		"SNMP access from LAN:
			0 - Decline,
			1 - Allow
		Device Allocation: AP, SM"
	DEFVAL	{ 1 }
	::= { l2Firewall 4 }

l2DHCPServersBelowSTA  OBJECT-TYPE
	SYNTAX	   Integer32 (0|1)
	MAX-ACCESS read-write
	STATUS	   current
	DESCRIPTION
		"Allow DHCP Servers Below SM:
			0 - Decline,
			1 - Allow
		Device Allocation: SM"
	DEFVAL	{ 0 }
	::= { l2Firewall 5 }

l2LanRemoteAccess  OBJECT-TYPE
	SYNTAX     Integer32 (0|1)
	MAX-ACCESS read-write
	STATUS     current
	DESCRIPTION
		"SM Management Access Through LAN:
			0 - Wireless Only,
			1 - Ethernet and Wireless
		Device Allocation: SM"
	DEFVAL  { 0 }
	::= { l2Firewall 6 }

l3FirewallEnable  OBJECT-TYPE
	SYNTAX	   Integer32 (0|1)
	MAX-ACCESS read-write
	STATUS	   current
	DESCRIPTION
		"L3 ACL Rule Status
			1 - Enable,
			0 - Disable
		Device Allocation: AP, SM"
	::= { l3Firewall 1 }

l3FirewallTable	 OBJECT-TYPE
	SYNTAX SEQUENCE OF L3FirewallEntry
	MAX-ACCESS not-accessible
	STATUS	   current
	DESCRIPTION
		"L3 Firewall Table
		Device Allocation: AP, SM"
	::= { l3Firewall 2 }

l3FirewallEntry	 OBJECT-TYPE
	SYNTAX	L3FirewallEntry
	MAX-ACCESS not-accessible
	STATUS	   current
	DESCRIPTION
		"L3 Firewall Table Entry
		Device Allocation: AP, SM"
	INDEX	{ l3FirewallEntryIndex }
	::= { l3FirewallTable 1 }

L3FirewallEntry ::= SEQUENCE {
	l3FirewallEntryIndex
		Integer32,
	l3FirewallEntryName
		DisplayString,
	l3FirewallEntryAction
		Integer32,
	l3FirewallEntryInterface
		Integer32,
	l3FirewallEntryLog
		Integer32,
	l3FirewallEntryProtocol
		Integer32,
	l3FirewallEntryPort
		Integer32,
	l3FirewallEntrySrcIP
		IpAddress,
	l3FirewallEntrySrcMask
		IpAddress,
	l3FirewallEntryDstIP
		IpAddress,
	l3FirewallEntryDstMask
		IpAddress,
	l3FirewallEntryDSCP
		Integer32,
	l3FirewallEntryToS
		Integer32,
	l3FirewallEntrySrcPort
		Integer32
}

l3FirewallEntryIndex  OBJECT-TYPE
	SYNTAX	   Integer32 (0..16)
	MAX-ACCESS read-write
	STATUS	   current
	DESCRIPTION
		"L3 ACL Table Index
		Table Entry is cleared if Index is set to zero
		Device Allocation: AP, SM"
	::= { l3FirewallEntry 1 }

l3FirewallEntryName	 OBJECT-TYPE
	SYNTAX	   DisplayString (SIZE(0|1..128))
	MAX-ACCESS read-write
	STATUS	   current
	DESCRIPTION
		"L3 ACL Rule Name
		Device Allocation: AP, SM"
	::= { l3FirewallEntry 2 }

l3FirewallEntryAction  OBJECT-TYPE
	SYNTAX	   Integer32 (0|1)
	MAX-ACCESS read-write
	STATUS	   current
	DESCRIPTION
		"L3 ACL Rule Acrion
			0 - Reject,
			1 - Permit
		Device Allocation: AP, SM"
	::= { l3FirewallEntry 3 }

l3FirewallEntryInterface  OBJECT-TYPE
	SYNTAX	   Integer32 (0|1|2)
	MAX-ACCESS read-write
	STATUS	   current
	DESCRIPTION
		"L3 ACL Rule Interface
			1 - WAN,
			2 - LAN
		Device Allocation: AP, SM"
	::= { l3FirewallEntry 4 }

l3FirewallEntryLog	OBJECT-TYPE
	SYNTAX	   Integer32 (0|1)
	MAX-ACCESS read-write
	STATUS	   current
	DESCRIPTION
		"L3 ACL Rule Log Flag
			1 - Rule Loggin is On,
			0 - Rule Logging is Off
		Device Allocation: AP, SM"
	::= { l3FirewallEntry 5 }

l3FirewallEntryProtocol	 OBJECT-TYPE
	SYNTAX	   Integer32 (0|1|2|3|4|5)
	MAX-ACCESS read-write
	STATUS	   current
	DESCRIPTION
		"L3 ACL Rules IP Protocol
			1 - TCP,
			2 - UDP,
			3 - TCP+UDP,
			4 - ICMP,
			5 - IP
		Device Allocation: AP, SM"
	::= { l3FirewallEntry 6 }

l3FirewallEntryPort	 OBJECT-TYPE
	SYNTAX	   Integer32 (0..65535)
	MAX-ACCESS read-write
	STATUS	   current
	DESCRIPTION
		"L3 ACL Rule Destination Port
		Device Allocation: AP, SM"
	::= { l3FirewallEntry 7 }

l3FirewallEntrySrcIP  OBJECT-TYPE
	SYNTAX	   IpAddress
	MAX-ACCESS read-write
	STATUS	   current
	DESCRIPTION
		"L3 ACL Rule Source IP Address
		Device Allocation: AP, SM"
	::= { l3FirewallEntry 8 }

l3FirewallEntrySrcMask	OBJECT-TYPE
	SYNTAX	   IpAddress
	MAX-ACCESS read-write
	STATUS	   current
	DESCRIPTION
		"L3 ACL Rule Source Network Mask
		Device Allocation: AP, SM"
	::= { l3FirewallEntry 9 }

l3FirewallEntryDstIP  OBJECT-TYPE
	SYNTAX	   IpAddress
	MAX-ACCESS read-write
	STATUS	   current
	DESCRIPTION
		"L3 ACL Rule Destination IP Address
		Device Allocation: AP, SM"
	::= { l3FirewallEntry 10 }

l3FirewallEntryDstMask	OBJECT-TYPE
	SYNTAX	   IpAddress
	MAX-ACCESS read-write
	STATUS	   current
	DESCRIPTION
		"L3 ACL Rule Destination Network Mask
		Device Allocation: AP, SM"
	::= { l3FirewallEntry 11 }

l3FirewallEntryDSCP	 OBJECT-TYPE
	SYNTAX	   Integer32 (0..63)
	MAX-ACCESS read-write
	STATUS	   current
	DESCRIPTION
		"L3 ACL Rule DSCP
		Device Allocation: AP, SM"
	::= { l3FirewallEntry 12 }

l3FirewallEntryToS	OBJECT-TYPE
	SYNTAX	   Integer32 (0..255)
	MAX-ACCESS read-write
	STATUS	   current
	DESCRIPTION
		"L3 ACL Rule TOS
		Device Allocation: AP, SM"
	::= { l3FirewallEntry 13 }

l3FirewallEntrySrcPort      OBJECT-TYPE
	SYNTAX     Integer32 (0..65535)
	MAX-ACCESS read-write
	STATUS     current
	DESCRIPTION
		"L3 ACL Rule Source Port
		Device Allocation: AP, SM"
	::= { l3FirewallEntry 14 }

dmzEnable  OBJECT-TYPE
	SYNTAX	   Integer32 (0|1)
	MAX-ACCESS read-write
	STATUS	   current
	DESCRIPTION
		"Enable DMZ:
			1 - Enable,
			0 - Disable.
		Device Allocation: SM"
	DEFVAL	{ 0 }
	::= { dmz 1 }

dmzIPAddress  OBJECT-TYPE
	SYNTAX	   IpAddress
	MAX-ACCESS read-write
	STATUS	   current
	DESCRIPTION
		"DMZ IP Address.
		Device Allocation: SM"
	::= { dmz 2 }

dmzAllowICMP	OBJECT-TYPE
	SYNTAX		Integer32 (0|1)
	MAX-ACCESS	read-write
	STATUS		current
	DESCRIPTION
		"Allow ICMP to DMZ
			0 - Disable (Allow ICMP to SM),
			1 - Enable  (Do not allow ICMP to SM)
		Device Allocation: SM"
	DEFVAL		{ 1 }
	::= { dmz 3 }

voipEnable	OBJECT-TYPE
	SYNTAX	   Integer32 (0|1)
	MAX-ACCESS read-write
	STATUS	   current
	DESCRIPTION
		"VoIP Enable:
			0 - disable,
			1 - enable
		Device Allocation: AP, SM"
	DEFVAL	{ 0 }
	::= { confQoS 1 }

qosEnable  OBJECT-TYPE
	SYNTAX	   Integer32 (0|1)
	MAX-ACCESS read-write
	STATUS	   current
	DESCRIPTION
		"Enable QoS:
			0 - disable,
			1 - enable
		Device Allocation: AP, SM"
	DEFVAL	{ 0 }
	::= { confQoS 2 }

classificationListTable	 OBJECT-TYPE
	SYNTAX SEQUENCE OF ClassificationListEntry
	MAX-ACCESS not-accessible
	STATUS	   current
	DESCRIPTION
		"Quality of Service rules Table
		Device Allocation: AP, SM"
	::= { confQoS 3 }

mcPriority	OBJECT-TYPE
	SYNTAX	   Integer32 (0|1)
	MAX-ACCESS read-write
	STATUS	   current
	DESCRIPTION
		"Multicast Priority:
			0 - low,
			1 - high
		Device Allocation: AP, SM"
	DEFVAL	{ 0 }
	::= { confQoS 4 }

bcPriority	OBJECT-TYPE
	SYNTAX	   Integer32 (0|1)
	MAX-ACCESS read-write
	STATUS	   current
	DESCRIPTION
		"Broadcast Priority:
			0 - low,
			1 - high
		Device Allocation: AP, SM"
	DEFVAL	{ 0 }
	::= { confQoS 5 }

classificationListEntry	 OBJECT-TYPE
	SYNTAX	ClassificationListEntry
	MAX-ACCESS not-accessible
	STATUS	   current
	DESCRIPTION
		"Quality of Service Rule Entry
		Device Allocation: AP, SM"
	INDEX	{ classificationRuleIndex }
	::= { classificationListTable 1 }

ClassificationListEntry ::= SEQUENCE {
	classificationRuleIndex
		Integer32,
	classificationRuleType
		Integer32,
	classificationRuleValue
		Integer32,
	classificationRuleIP
		IpAddress,
	classificationRuleMAC
		DisplayString,
	classificationRuleMask
		DisplayString,
	classificationRuleDirection
		Integer32,
	classificationRuleQueue
		Integer32
}

classificationRuleIndex	 OBJECT-TYPE
	SYNTAX	   Integer32 (0..14)
	MAX-ACCESS read-write
	STATUS	   current
	DESCRIPTION
		"QoS Rule Table Index
		Table Entry is cleared if Index is set to zero
		Device Allocation: AP, SM"
	::= { classificationListEntry 1 }

classificationRuleType	OBJECT-TYPE
	SYNTAX	   Integer32 (0|1..9)
	MAX-ACCESS read-write
	STATUS	   current
	DESCRIPTION
		"QoS Rule Type:
			1 - voip,
			2 - dscp,
			3 - cos,
			4 - vlanid,
			5 - ethertype,
			6 - ipv4,
			7 - mac,
			8 - broadcast,
			9 - multicast
		Device Allocation: AP, SM"
	::= { classificationListEntry 2 }

classificationRuleValue	 OBJECT-TYPE
	SYNTAX	   Integer32 (0..65535)
	MAX-ACCESS read-write
	STATUS	   current
	DESCRIPTION
		"QoS Rule Value. Qos rule value is valid only for dscp, cos, vlanid and ethertype Rule types
		Device Allocation: AP, SM"
	::= { classificationListEntry 3 }

classificationRuleIP  OBJECT-TYPE
	SYNTAX	   IpAddress
	MAX-ACCESS read-write
	STATUS	   current
	DESCRIPTION
		"QoS IP Address
		Device Allocation: AP, SM"
	::= { classificationListEntry 4 }

classificationRuleMAC  OBJECT-TYPE
	SYNTAX	   DisplayString (SIZE(0|17))
	MAX-ACCESS read-write
	STATUS	   current
	DESCRIPTION
		"QoS MAC Address
		Device Allocation: AP, SM"
	::= { classificationListEntry 5 }

classificationRuleMask	OBJECT-TYPE
	SYNTAX	   DisplayString (SIZE(0|7..17))
	MAX-ACCESS read-write
	STATUS	   current
	DESCRIPTION
		"QoS Netmask
		Device Allocation: AP, SM"
	::= { classificationListEntry 6 }

classificationRuleDirection	 OBJECT-TYPE
	SYNTAX	   Integer32 (0|1..3)
	MAX-ACCESS read-write
	STATUS	   current
	DESCRIPTION
		"IP or MAC Rules direction:
			1 - Source,
			2 - Destination,
			3 - Either (or Both directions)
		Device Allocation: AP, SM"
	::= { classificationListEntry 7 }

classificationRuleQueue	 OBJECT-TYPE
	SYNTAX	   Integer32 (0|1..3)
	MAX-ACCESS read-write
	STATUS	   current
	DESCRIPTION
		"Rule Queue:
			1- Hight,
			2 - Low,
			3 - VoIP
		Device Allocation: AP, SM"
	::= { classificationListEntry 8 }

portForwardingEntryEnable  OBJECT-TYPE
	SYNTAX	   Integer32 (0|1)
	MAX-ACCESS read-write
	STATUS	   current
	DESCRIPTION
		"Port Forwarding feature:
			0 - Disable,
			1 - Enable
		Device Allocation: SM"
	::= { portForwarding 1 }

portForwardingTable	 OBJECT-TYPE
	SYNTAX SEQUENCE OF PortForwardingEntry
	MAX-ACCESS not-accessible
	STATUS	   current
	DESCRIPTION
		"Port Forwarding Rules Table
		Device Allocation: SM"
	::= { portForwarding 2 }

portForwardingEntry	 OBJECT-TYPE
	SYNTAX	PortForwardingEntry
	MAX-ACCESS not-accessible
	STATUS	   current
	DESCRIPTION
		"Port Forwarding Table Rule Entry
		Device Allocation: SM"
	INDEX	{ portForwardingTableEntryIndex }
	::= { portForwardingTable 1 }

PortForwardingEntry ::= SEQUENCE {
	portForwardingTableEntryIndex
		Integer32,
	portForwardingTableEntryProtocol
		Integer32,
	portForwardingTableEntryWLANPortBegin
		Integer32,
	portForwardingTableEntryWLANPortEnd
		Integer32,
	portForwardingTableEntryLANIP
		IpAddress,
	portForwardingTableEntryWLANPortMappedBegin
		Integer32
}

portForwardingTableEntryIndex  OBJECT-TYPE
	SYNTAX	   Integer32 (0..32)
	MAX-ACCESS read-write
	STATUS	   current
	DESCRIPTION
		"Port Forwarding Table Entry Index
		Table Entry is cleared if Index is set to zero
		Device Allocation: SM"
	::= { portForwardingEntry 1 }

portForwardingTableEntryProtocol  OBJECT-TYPE
	SYNTAX	   Integer32 (0|1|2|3)
	MAX-ACCESS read-write
	STATUS	   current
	DESCRIPTION
		"Port Forwarding Table Entry Rule Protocol:
			0 - Clear Rule,
			1 - UDP,
			2 - TCP,
			3 - UDP+TCP
		Device Allocation: SM"
	::= { portForwardingEntry 2 }

portForwardingTableEntryWLANPortBegin  OBJECT-TYPE
	SYNTAX	   Integer32 (0..65535)
	MAX-ACCESS read-write
	STATUS	   current
	DESCRIPTION
		"Port Forwarding WLAN Port Start number
		Device Allocation: SM"
	::= { portForwardingEntry 3 }

portForwardingTableEntryWLANPortEnd	 OBJECT-TYPE
	SYNTAX	   Integer32 (0..65535)
	MAX-ACCESS read-write
	STATUS	   current
	DESCRIPTION
		"Port Forwarding WLAN Port End number
		Device Allocation: SM"
	::= { portForwardingEntry 4 }

portForwardingTableEntryLANIP  OBJECT-TYPE
	SYNTAX	   IpAddress
	MAX-ACCESS read-write
	STATUS	   current
	DESCRIPTION
		"Port Forwarding LAN IP Address
		Device Allocation: SM"
	::= { portForwardingEntry 5 }

portForwardingTableEntryWLANPortMappedBegin  OBJECT-TYPE
	SYNTAX     Integer32 (0..65535)
	MAX-ACCESS read-write
	STATUS     current
	DESCRIPTION
		"Port Forwarding Mapped Port number
		Device Allocation: SM"
	::= { portForwardingEntry 6 }

portForwardingSepMangIPEntryEnable  OBJECT-TYPE
	SYNTAX     Integer32 (0|1)
	MAX-ACCESS read-write
	STATUS     current
	DESCRIPTION
		"SM Separate Management IP Port Forwarding feature:
			0 - Disable,
			1 - Enable
		Device Allocation: SM"
	::= { portForwarding 3 }

portForwardingSepMangIPTable      OBJECT-TYPE
	SYNTAX SEQUENCE OF PortForwardingSepMangIPEntry
	MAX-ACCESS not-accessible
	STATUS     current
	DESCRIPTION
		"SM Separate Management IP Port Forwarding Rules Table
		Device Allocation: SM"
	::= { portForwarding 4 }

portForwardingSepMangIPEntry      OBJECT-TYPE
	SYNTAX  PortForwardingSepMangIPEntry
	MAX-ACCESS not-accessible
	STATUS     current
	DESCRIPTION
		"SM Separate Management IP Port Forwarding Table Rule Entry
		Device Allocation: SM"
	INDEX   { portForwardingSepMangIPTableEntryIndex }
	::= { portForwardingSepMangIPTable 1 }

PortForwardingSepMangIPEntry ::= SEQUENCE {
	portForwardingSepMangIPTableEntryIndex
		Integer32,
	portForwardingSepMangIPTableEntryProtocol
		Integer32,
	portForwardingSepMangIPTableEntryWLANPortBegin
		Integer32,
	portForwardingSepMangIPTableEntryWLANPortEnd
		Integer32,
	portForwardingSepMangIPTableEntryLANIP
		IpAddress,
	portForwardingSepMangIPTableEntryWLANPortMappedBegin
		Integer32
}

portForwardingSepMangIPTableEntryIndex  OBJECT-TYPE
	SYNTAX     Integer32 (0..16)
	MAX-ACCESS read-write
	STATUS     current
	DESCRIPTION
		"SM Separate Management IP Port Forwarding Table Entry Index
		Table Entry is cleared if Index is set to zero
		Device Allocation: SM"
	::= { portForwardingSepMangIPEntry 1 }

portForwardingSepMangIPTableEntryProtocol  OBJECT-TYPE
	SYNTAX     Integer32 (0|1|2|3)
	MAX-ACCESS read-write
	STATUS     current
	DESCRIPTION
		"SM Separate Management IP Port Forwarding Table Entry Rule Protocol:
			0 - Clear Rule,
			1 - UDP,
			2 - TCP,
			3 - UDP+TCP
		Device Allocation: SM"
	::= { portForwardingSepMangIPEntry 2 }

portForwardingSepMangIPTableEntryWLANPortBegin  OBJECT-TYPE
	SYNTAX     Integer32 (0..65535)
	MAX-ACCESS read-write
	STATUS     current
	DESCRIPTION
		"SM Separate Management IP Port Forwarding WLAN Port Start number
		Device Allocation: SM"
	::= { portForwardingSepMangIPEntry 3 }

portForwardingSepMangIPTableEntryWLANPortEnd      OBJECT-TYPE
	SYNTAX     Integer32 (0..65535)
	MAX-ACCESS read-write
	STATUS     current
	DESCRIPTION
		"SM Separate Management IP Port Forwarding WLAN Port End number
		Device Allocation: SM"
	::= { portForwardingSepMangIPEntry 4 }

portForwardingSepMangIPTableEntryLANIP  OBJECT-TYPE
	SYNTAX     IpAddress
	MAX-ACCESS read-write
	STATUS     current
	DESCRIPTION
		"SM Separate Management IP Port Forwarding LAN IP Address
		Device Allocation: SM"
	::= { portForwardingSepMangIPEntry 5 }

portForwardingSepMangIPTableEntryWLANPortMappedBegin  OBJECT-TYPE
	SYNTAX     Integer32 (0..65535)
	MAX-ACCESS read-write
	STATUS     current
	DESCRIPTION
		"SM Separate Management IP Port Forwarding Mapped Port number
		Device Allocation: SM"
	::= { portForwardingSepMangIPEntry 6 }

staticRoutesEnableMain	 OBJECT-TYPE
	SYNTAX		Integer32 (0|1)
	MAX-ACCESS	read-write
	STATUS		current
	DESCRIPTION
		"Static Routes trigger
			0 - Disable
			1 - Enable"
	DEFVAL	{ 0 }
	::= { routing 1 }

cambiumStaticRoutesCnfTable	 OBJECT-TYPE
	SYNTAX SEQUENCE OF CambiumStaticRoutesCnfEntry
	MAX-ACCESS not-accessible
	STATUS	   current
	DESCRIPTION
		"Static Routes Table"
	::= { routing 2 }

cambiumTelnetServerEnable  OBJECT-TYPE
	SYNTAX     Integer32 (0|1)
	MAX-ACCESS read-write
	STATUS     current
	DESCRIPTION
		"Cambium Telnet Server:
			0 - Disable,
			1 - Enable
		Device Allocation: AP, SM"
	DEFVAL  { 0 }
	::= { cambiumTelnetServer 1 }

cambiumTelnetServerPort  OBJECT-TYPE
	SYNTAX     Integer32 (1..65535)
	MAX-ACCESS read-write
	STATUS     current
	DESCRIPTION
		"Cambium Telnet Server Port Number.
		Device Allocation: AP, SM"
	DEFVAL  { 23 }
	::= { cambiumTelnetServer 2 }

cambiumDeviceAgentEnable  OBJECT-TYPE
	SYNTAX		Integer32 (0|1)
	MAX-ACCESS	read-write
	STATUS		current
	DESCRIPTION
		"Remote Management:
			0 - Disable
			1 - Enable
		Cambium provides cloud management of Cambium devices called cnMaestro.
		This allows a user to manage all of their various Cambium devices via the web from any location in the world.
		This field enables this cnMaestro Cloud Management."
	DEFVAL	{ 1 }
	::= { cambiumDeviceAgent 1 }

cambiumDeviceAgentCNSURL  OBJECT-TYPE
	SYNTAX	   OCTET STRING (SIZE(0..128))
	MAX-ACCESS read-write
	STATUS	   current
	DESCRIPTION
		"cnMaestro URL:
		 This specifies the URL for accessing the cnMaestro Cloud Manager"
	::= { cambiumDeviceAgent 2 }

cambiumCNSDeviceAgentID  OBJECT-TYPE
	SYNTAX     OCTET STRING (SIZE(0..128))
	MAX-ACCESS read-write
	STATUS     current
	DESCRIPTION
		"Cambium ID:
		This is a user name for the cnMaestro Remote Management system.
		This is used with the 'Onboarding Key' to on-board older Cambium devices,
		which are not provisioned with an MSN in the Cambium factory."
	::= { cambiumDeviceAgent 3 }

cambiumCNSDeviceAgentPassword  OBJECT-TYPE
	SYNTAX     OCTET STRING (SIZE(0..128))
	MAX-ACCESS read-write
	STATUS     current
	DESCRIPTION
		"Onboarding Key:
		This is a password for the cnMaestro Remote Management system.
		This is used with the 'Cambium ID' to on-board older Cambium devices,
		which are not provisioned with an MSN in the Cambium factory."
	::= { cambiumDeviceAgent 4 }

cambiumDeviceAgentZeroTouchEnable  OBJECT-TYPE
	SYNTAX		Integer32 (0|1)
	MAX-ACCESS	read-write
	STATUS		current
	DESCRIPTION
		"Zero Touch:
			0 - Disable
			1 - Enable
		Zero Touch feature provides every associated SM
		with credentials to establish connection with cnMaestro.
		Device Allocation: AP"
	DEFVAL	{ 1 }
	::= { cambiumDeviceAgent 5 }

cambiumDeviceAgentMGMTRoutingEnable  OBJECT-TYPE
	SYNTAX		Integer32 (0|1)
	MAX-ACCESS	read-write
	STATUS		current
	DESCRIPTION
		"Routing Device Agent traffic through Separate Management Interface:
			0 - Disable
			1 - Enable
		Device Allocation: SM"
	DEFVAL	{ 0 }
	::= { cambiumDeviceAgent 6 }

cambiumStaticRoutesCnfEntry OBJECT-TYPE
	SYNTAX	   CambiumStaticRoutesCnfEntry
	MAX-ACCESS not-accessible
	STATUS	   current
	DESCRIPTION
		"Static Routes Dest/Getway pair entry"
	INDEX	{ cambiumStaticRoutesCnfIndex }
	::= { cambiumStaticRoutesCnfTable 1 }

CambiumStaticRoutesCnfEntry ::= SEQUENCE {
	cambiumStaticRoutesCnfIndex
		Integer32,
	cambiumStaticRoutesCnfDestIP
		IpAddress,
	cambiumStaticRoutesCnfGW
		IpAddress,
	cambiumStaticRoutesCnfNetmask
		IpAddress,
	cambiumStaticRoutesCnfEnbl
		Integer32,
	cambiumStaticRoutesCnfInfo
		DisplayString
}

cambiumStaticRoutesCnfIndex	 OBJECT-TYPE
	SYNTAX	  Integer32 (0..16)
	MAX-ACCESS read-write
	STATUS	   current
	DESCRIPTION
		"Index"
	::= { cambiumStaticRoutesCnfEntry 1 }

cambiumStaticRoutesCnfDestIP  OBJECT-TYPE
	SYNTAX	   IpAddress
	MAX-ACCESS read-write
	STATUS	   current
	DESCRIPTION
		"Destination IP"
	::= { cambiumStaticRoutesCnfEntry 2 }

cambiumStaticRoutesCnfGW  OBJECT-TYPE
	SYNTAX	   IpAddress
	MAX-ACCESS read-write
	STATUS	   current
	DESCRIPTION
		"Getway IP"
	::= { cambiumStaticRoutesCnfEntry 3 }

cambiumStaticRoutesCnfNetmask  OBJECT-TYPE
	SYNTAX	   IpAddress
	MAX-ACCESS read-write
	STATUS	   current
	DESCRIPTION
		"Dest IP Netmask"
	::= { cambiumStaticRoutesCnfEntry 4 }

cambiumStaticRoutesCnfEnbl	OBJECT-TYPE
	SYNTAX	   Integer32 (0|1)
	MAX-ACCESS read-write
	STATUS	   current
	DESCRIPTION
		"Static Routes enable an entry"
	::= { cambiumStaticRoutesCnfEntry 5 }

cambiumStaticRoutesCnfInfo	OBJECT-TYPE
	SYNTAX	   DisplayString (SIZE(0..100))
	MAX-ACCESS read-write
	STATUS	   current
	DESCRIPTION
		"Static Routes Interface Name"
	::= { cambiumStaticRoutesCnfEntry 6 }


mgmtVLANEnable	OBJECT-TYPE
	SYNTAX	   Integer32 (0|1)
	MAX-ACCESS read-write
	STATUS	   current
	DESCRIPTION
		"Management VLANs State:
			0 - Disable,
			1 - Enable
		Device Allocation: AP, SM"
	DEFVAL	{ 0 }
	::= { mgmtVLAN 1 }

mgmtVLANVID	 OBJECT-TYPE
	SYNTAX	   Integer32 (1..4094)
	MAX-ACCESS read-write
	STATUS	   current
	DESCRIPTION
		"Management VLAN ID
		Device Allocation: AP, SM"
	::= { mgmtVLAN 2 }

mgmtVLANVP	OBJECT-TYPE
	SYNTAX	   Integer32 (0..7)
	MAX-ACCESS read-write
	STATUS	   current
	DESCRIPTION
		"Management VLAN VP
		Device Allocation: AP, SM"
	::= { mgmtVLAN 3 }

dataVLANEnable	OBJECT-TYPE
	SYNTAX	   Integer32 (0|1)
	MAX-ACCESS read-write
	STATUS	   current
	DESCRIPTION
		"Data VLANs State:
			0 - Disable,
			1 - Enable
		Device Allocation: SM"
	DEFVAL	{ 0 }
	::= { dataVLAN 1 }

dataVLANVID	 OBJECT-TYPE
	SYNTAX	   Integer32 (1..4094)
	MAX-ACCESS read-write
	STATUS	   current
	DESCRIPTION
		"Data VLAN ID
		Device Allocation: SM"
	::= { dataVLAN 2 }

dataVLANVP	OBJECT-TYPE
	SYNTAX	   Integer32 (0..7)
	MAX-ACCESS read-write
	STATUS	   current
	DESCRIPTION
		"Data VLAN VP
		Device Allocation: SM"
	::= { dataVLAN 3 }

mcastVLANEnable	 OBJECT-TYPE
	SYNTAX	   Integer32 (0|1)
	MAX-ACCESS read-write
	STATUS	   current
	DESCRIPTION
		"Multicast VLAN State:
			0 - Disable,
			1 - Enable
		Device Allocation: SM"
	DEFVAL	{ 0 }
	::= { mcastVLAN 1 }

mcastVLANVID  OBJECT-TYPE
	SYNTAX	   Integer32 (1..4094)
	MAX-ACCESS read-write
	STATUS	   current
	DESCRIPTION
		"Multicast VLAN ID
		Device Allocation: SM"
	::= { mcastVLAN 2 }

mcastVLANVP	 OBJECT-TYPE
	SYNTAX	   Integer32 (0..7)
	MAX-ACCESS read-write
	STATUS	   current
	DESCRIPTION
		"Multicast VLAN VP
		Device Allocation: SM"
	::= { mcastVLAN 3 }

membershipVLANTable	 OBJECT-TYPE
	SYNTAX SEQUENCE OF MembershipVLANEntry
	MAX-ACCESS not-accessible
	STATUS	   current
	DESCRIPTION
		"Membership VLAN Rules Table
		Device Allocation: SM"
	::= { vlans 3 }

membershipVLANEntry	 OBJECT-TYPE
	SYNTAX	MembershipVLANEntry
	MAX-ACCESS not-accessible
	STATUS	   current
	DESCRIPTION
		"Membership VLAN Table Rule Entry
		Device Allocation: SM"
	INDEX	{ membershipVLANTableEntryIndex }
	::= { membershipVLANTable 1 }

MembershipVLANEntry ::= SEQUENCE {
	membershipVLANTableEntryIndex
		Integer32,
	membershipVLANTableEntryVIDBegin
		Integer32,
	membershipVLANTableEntryVIDEnd
		Integer32,
	membershipVLANTableEntryInfo
		DisplayString
}

membershipVLANTableEntryIndex  OBJECT-TYPE
	SYNTAX	   Integer32 (0..16)
	MAX-ACCESS read-write
	STATUS	   current
	DESCRIPTION
		"Membership VLAN Table Entry Index
		Table Entry is cleared if Index is set to zero
		Device Allocation: SM"
	::= { membershipVLANEntry 1 }

membershipVLANTableEntryVIDBegin  OBJECT-TYPE
	SYNTAX	   Integer32 (0|1..4095)
	MAX-ACCESS read-write
	STATUS	   current
	DESCRIPTION
		"Membership VLAN Table Entry VLAN ID Begin
		Device Allocation: SM"
	::= { membershipVLANEntry 2 }

membershipVLANTableEntryVIDEnd	OBJECT-TYPE
	SYNTAX	   Integer32 (0|1..4095)
	MAX-ACCESS read-write
	STATUS	   current
	DESCRIPTION
		"Membership VLAN Table Entry VLAN ID End
		Device Allocation: SM"
	::= { membershipVLANEntry 3 }

membershipVLANTableEntryInfo OBJECT-TYPE
	SYNTAX	   DisplayString (SIZE(0|1..128))
	MAX-ACCESS read-write
	STATUS	   current
	DESCRIPTION
		"Membership VLAN Table Entry Description.
		Device Allocation: SM"
	::= { membershipVLANEntry 4 }

mappingVLANTable  OBJECT-TYPE
	SYNTAX SEQUENCE OF MappingVLANEntry
	MAX-ACCESS not-accessible
	STATUS	   current
	DESCRIPTION
		"Mapping VLAN Rules Table
		Device Allocation: SM"
	::= { vlans 5 }

mappingVLANEntry  OBJECT-TYPE
	SYNTAX	MappingVLANEntry
	MAX-ACCESS not-accessible
	STATUS	   current
	DESCRIPTION
		"Mapping VLAN Table Rule Entry
		Device Allocation: SM"
	INDEX	{ mappingVLANTableEntryIndex }
	::= { mappingVLANTable 1 }

MappingVLANEntry ::= SEQUENCE {
	mappingVLANTableEntryIndex
		Integer32,
	mappingVLANTableEntryCVLAN
		Integer32,
	mappingVLANTableEntrySVLAN
		Integer32,
	mappingVLANTableEntryInfo
		DisplayString
}

mappingVLANTableEntryIndex	OBJECT-TYPE
	SYNTAX	   Integer32 (0..16)
	MAX-ACCESS read-write
	STATUS	   current
	DESCRIPTION
		"Mapping VLAN Table Entry Index
		Table Entry is cleared if Index is set to zero
		Device Allocation: SM"
	::= { mappingVLANEntry 1 }

mappingVLANTableEntryCVLAN	OBJECT-TYPE
	SYNTAX	   Integer32 (0|1..4095)
	MAX-ACCESS read-write
	STATUS	   current
	DESCRIPTION
		"Mapping VLAN Table C-VLAN ID,
		 Defines VLAN ID to be mapped from CPE side.
		Device Allocation: SM"
	::= { mappingVLANEntry 2 }

mappingVLANTableEntrySVLAN  OBJECT-TYPE
	SYNTAX     Integer32 (0|1..4095)
	MAX-ACCESS read-write
	STATUS     current
	DESCRIPTION
		"Mapping VLAN Table S-VLAN ID,
		 Defines VLAN ID to be mapped from Service provider.
		Device Allocation: SM"
	::= { mappingVLANEntry 3 }

mappingVLANTableEntryInfo  OBJECT-TYPE
	SYNTAX     DisplayString (SIZE(0|1..128))
	MAX-ACCESS read-write
	STATUS     current
	DESCRIPTION
		"Mapping VLAN Table Entry Description.
		Device Allocation: SM"
	::= { mappingVLANEntry 4 }

dlkmNATSIPHelpers OBJECT-TYPE
	SYNTAX     Integer32 (0|1)
	MAX-ACCESS read-write
	STATUS     current
	DESCRIPTION
		"Enables Auxiliary Netfilter NAT SIP Helper modules support:
			0 - Disable,
			1 - Enabled
		Device Allocation: AP, SM"
	::= { dlkm 1 }

prefferedAPTable OBJECT-TYPE
	SYNTAX SEQUENCE OF PrefferedAPEntry
	MAX-ACCESS not-accessible
	STATUS	   current
	DESCRIPTION
		"Preffered AP Table
		Device Allocation: SM"
	::= { wirelessPrefList 1 }

prefferedAPEntry  OBJECT-TYPE
	SYNTAX	PrefferedAPEntry
	MAX-ACCESS not-accessible
	STATUS	   current
	DESCRIPTION
		"Preffered SSID Table Entry
		Device Allocation: SM"
	INDEX	{ prefferedListTableEntryIndex }
	::= { prefferedAPTable 1 }

PrefferedAPEntry ::= SEQUENCE {
	prefferedListTableEntryIndex
		Integer32,
	prefferedListTableEntrySSID
		OCTET STRING,
	prefferedListTableEntryKEY
		OCTET STRING,
	prefferedListTableSecurityMethod
		Integer32
}

prefferedListTableEntryIndex  OBJECT-TYPE
	SYNTAX	   Integer32 (0..16)
	MAX-ACCESS read-write
	STATUS	   current
	DESCRIPTION
		"Preferred AP Table Index
		Table Entry is cleared if Index is set to zero
		Device Allocation: SM"
	::= { prefferedAPEntry 1 }

prefferedListTableEntrySSID	 OBJECT-TYPE
	SYNTAX	   OCTET STRING (SIZE(0|1..32))
	MAX-ACCESS read-write
	STATUS	   current
	DESCRIPTION
		"Preferred AP SSID
		Device Allocation: SM"
	::= { prefferedAPEntry 2 }

prefferedListTableEntryKEY	OBJECT-TYPE
	SYNTAX	   OCTET STRING (SIZE(0|8..63))
	MAX-ACCESS read-write
	STATUS	   current
	DESCRIPTION
		"Preferred AP Shared Key
		Device Allocation: SM"
	::= { prefferedAPEntry 3 }

prefferedListTableSecurityMethod  OBJECT-TYPE
	SYNTAX	   Integer32(0..6)
	MAX-ACCESS read-write
	STATUS	   current
	DESCRIPTION
		"Authentication modes to connect to AP
		Device Allocation: SM
		Use bitmask to enable pereferred methods, 0 - means enable method:
		set 0-th bit to 0 - Open method (110b)
		set 1-st bit to 0 - WPA2 method (101b)
		set 2-nd bit to 0 - EAP-TTLS method (011b)
		0x00 - All enabled"
	DEFVAL	{ 0 }
	::= { prefferedAPEntry 4 }


cambiumpmp80211DeviceReboot	 OBJECT-TYPE
	SYNTAX	   Integer32 (1)
	MAX-ACCESS read-write
	STATUS	   current
	DESCRIPTION
		"OID for Device Reboot, send reboot command to device
		Device Allocation: AP, SM"
	::= { cambiumpmp80211SystemActions 1 }

cambiumpmp80211ConfigurationReset  OBJECT-TYPE
	SYNTAX	   Integer32 (0..7)
	MAX-ACCESS read-write
	STATUS	   current
	DESCRIPTION
		"OID for System Configuration reset to Defaults
		Device Allocation: AP, SM
		Use bitmask to enable options:
		set 0-th bit to 1 to do reset at all (001b)
		set 1-st bit to 1 to preserve license (011b)
		set 2-nd bit to 1 to preserve passwords (101b)"
	::= { cambiumpmp80211SystemActions 2 }

cambiumpmp80211ConfigurationSave  OBJECT-TYPE
	SYNTAX	   Integer32 (1)
	MAX-ACCESS read-write
	STATUS	   current
	DESCRIPTION
		"OID for configuration save
		Device Allocation: AP, SM"
	::= { cambiumpmp80211SystemActions 3 }

-- OID for configuration Apply action

cambiumpmp80211ConfigurationApply  OBJECT-TYPE
	SYNTAX	   Integer32 (1)
	MAX-ACCESS read-write
	STATUS	   current
	DESCRIPTION
		"OID for configuration Apply
		Device Allocation: AP, SM"
	::= { cambiumpmp80211SystemActions 4 }

cambiumpmp80211ConfigurationDiscard	 OBJECT-TYPE
	SYNTAX	   Integer32 (1)
	MAX-ACCESS read-write
	STATUS	   current
	DESCRIPTION
		"OID for configuration Discard
		Device Allocation: AP, SM"
	::= { cambiumpmp80211SystemActions 5 }

cambiumpmp80211ConfigurationState  OBJECT-TYPE
	SYNTAX	   Integer32 (0..255)
	MAX-ACCESS read-only
	STATUS	   current
	DESCRIPTION
		"System configuration state OID.
		Bit masks:
			0000 0001 - System is configured.
			0000 0010 - There are unsaved changesets.
			0000 0100 - There are unrestarted services.
			0000 1000 - Needed reboot of the system.
			0001 0000 - Configurations was reset.
			0010 0000 - Services restarting in process.
			0100 0000 - Software Update performed.
			1000 0000 - IP Address or protocol was changed.
		Device Allocation: AP, SM"
	::= { cambiumpmp80211SystemActions 6 }

cambiumpmp80211SoftwareUpdate  OBJECT-TYPE
	SYNTAX	   OCTET STRING
	MAX-ACCESS read-write
	STATUS	   current
	DESCRIPTION
		"System OID for Software Update Agent,
		SW Update link value can be either remote firmware link (http, https, ftp),
		or local file link: /tmp/firmware.tar.gz
		NOTE: Device is automatically rebooted if link type is remote
		Device Allocation: AP, SM"
	::= { cambiumpmp80211SystemActions 7 }

cambiumpmp80211SoftwareUpdateStatus	 OBJECT-TYPE
	SYNTAX	   Integer32 (0..10)
	MAX-ACCESS read-only
	STATUS	   current
	DESCRIPTION
		"Software Update Status OID
			0 - No SW Update is pending or No SW upgrade occurs,
			1 - SW Update is in progress, Uploading image to device,
			2 - SW Update is in progress, Verifying SHA2 signature,
			3 - SW Update is in progress, Executing pre-update script,
			4 - SW Update is in progress, Uploading image to flash,
			5 - SW Update is in progress, Uploading u-boot to flash,
			6 - SW Update is in progress, Executing post-update script,
			7 - SW Update is finished, waiting for reboot,
			8 - SW Update is in progress, Executing config down-grade script,
			9 - SW Update is in progress, Uploading firmware to flash & Reboot,
			10 - SW Update is in progress, Rebooting...
		When SW Update is successfully, return value is 7 for ePMP 1000/2000,
		and 9 for ePMP Elevate
		GUI or NMS indicate that SW update was successful,
		Device can be rebooted.
		Device Allocation: AP, SM"
	::= { cambiumpmp80211SystemActions 8 }

cambiumpmp80211STAListUpdate  OBJECT-TYPE
	SYNTAX	   Integer32 (1)
	MAX-ACCESS read-write
	STATUS	   current
	DESCRIPTION
		"System OID for SM List update
		When this OID is received,
		Connected SM list table is getting updated with actual SM list
		Device Allocation: AP"
	::= { cambiumpmp80211SystemActions 9 }

cambiumpmp80211STAListUpdateStatus	OBJECT-TYPE
	SYNTAX	   Integer32 (0|1|2)
	MAX-ACCESS read-write
	STATUS	   current
	DESCRIPTION
		"Sta List Update Status OID.
		This OID is used to indicate SM list table status:
			0 - No SMs are registerd to AP
			1 - SM List Table is getting updated
			2 - SM Data is ready
		Device Allocation: AP"
	::= { cambiumpmp80211SystemActions 10 }

cambiumpmp80211APListUpdate	 OBJECT-TYPE
	SYNTAX	   Integer32 (1)
	MAX-ACCESS read-write
	STATUS	   current
	DESCRIPTION
		"System OID for AP List update
		When this OID is received,
		Scanned AP list table is getting updated with actual AP scan list
		Device Allocation: SM"
	::= { cambiumpmp80211SystemActions 11 }

cambiumpmp80211APListUpdateStatus  OBJECT-TYPE
	SYNTAX	   Integer32 (0|1|2)
	MAX-ACCESS read-write
	STATUS	   current
	DESCRIPTION
		"AP List Update Status OID.
		This OID is used to indicate AP list table status:
			0 - No APs are available in the list
			1 - AP List Table is getting updated
			2 - AP Data is ready
		Device Allocation: SM"
	::= { cambiumpmp80211SystemActions 12 }

cambiumpmp80211SoftwareUpdateError  OBJECT-TYPE
	SYNTAX     Integer32
	MAX-ACCESS read-only
	STATUS     current
	DESCRIPTION
	  "Software Update error code:
		0 - Finished successfully, waiting for reboot.
		1 - SW update file download failed.
		2 - Unpack failed, damaged or wrong format package.
		3 - Firmware digital signature check failed.
		4 - U-Boot digital signature check failed.
		5 - Firmware FLASH write failed.
		6 - U-Boot FLASH write failed.
		7 - Boot partition switch failed.
		8 - Board SKU is not supported for this firmware.
		9 - Can't read firmware version, upgrade is impossible.
		10 - Down-grade not supported for WiFi & ePTP modes.
		11 - Down-grade below 2.3.1 is not supported for AP Lite device.
		12 - Down-grade not supported for non SM TDD mode.
		13 - Down-grade below 2.4.2 not supported for Force180/200 board types.
		14 - Down-grade below 2.5.0 not supported for AP WiFi.
		15 - Down-grade below 2.4.3 not supported for Reset Via Power Sequence.
		16 - Down-grade below 2.4.3 not supported for Particular Country Locked device.
		17 - Down-grade below 2.5.0 not supported for 2.5ms mode.
		18 - Down-grade below 2.5.2 not supported for Use MAC Address as EAP-TTLS Username.
		19 - Down-grade below 2.6.0 not supported for 5/10Mhz BW for WiFi & ePTP mode.
		20 - Separate Management IP Port Forwarding and Data Port Mapping are not supported in SW versions below 2.6.0.
		21 - General error. Device has no free memory.
		22 - General error code.
		23 - Downgrade below release 3.0 is not supported for ePMP2000.
		24 - Incorrect firmware type for the current device type.
		25 - Firmware file format is wrong for the current device type.
		26 - Downgrade below 5.6.6 is not supported for ePMP-Elevate board type.
		27 - Downgrade below 3.0.1 is not supported for 2.5G board type.
		28 - Downgrade below 3.1 is not supported if Preffered AP Table contains SSIDs with spaces.
		29 - Manifest Digital signature check failed.
		30 - Downgrade below 3.4 is not supported for Force 190 boards.
		31 - Downgrade below 3.5.2 is not supported for 6 GHz board type.
		32 - Downgrade below 3.4 is not supported for Elevate 2.4 GHz board.
		33 - Versions below 3.5 do not support License Server. Disable the License Server option before downgrade.
		34 - Opening binary sw-upgrader failed.
		35 - General error of upgrade process.
		36 - Channel Bonding is not supported in SW versions below 4.1.1.
		37 - 80 MHz channel bandwidth is not supported in SW versions below 4.1.1.
		38 - NAT and Router modes are not supported in SW versions below 4.3.
		39 - Downgrade below 3.5.4 is not supported for 802.11n devices and below 4.3 for 802.11ac devices with MAC addresses from pool 58:C1:7A:xx:xx:xx.
		40 - MTU value other than 1538 is not supported in SW versions below 4.1.3.
		41 - Downgrade below 4.3 is not supported for Force 300-16 boards.
		42 - Membership VLAN/VLAN Mapping is not supported in SW versions below 4.3.
		43 - Downgrade below 4.3 is not supported for ePMP3000 boards.
		44 - 40 or 80 MHz channel bandwidth is not supported for ePMP3000 in SW versions below 4.3.1.
		45 - Cannot upgrade this device with IPv6 enabled.
		46 - Software Upgrade is Rejected because Trial Configuration is in progress.
		47 - Downgrade below 4.4 is not supported for Force 300-13 or Force 300-19 boards.
		48 - Downgrade below 4.5 is not supported for ePMP MP 3000 board.
		49 - ePTP mode is not supported in SW versions below 4.5.
		50 - 2.5 ms mode is not supported in SW versions below 4.6.
		51 - 5/10Mhz BW mode is not supported in SW versions below 4.5.
		52 - Reliable multicast is not supported in SW versions below 4.5.
		53 - ACS is not supported in SW versions below 4.5.
		54 - Standard WiFi Driver Mode is not supported in SW versions below 4.5.
		55 - Omni/Split-Sector Antenna is not supported in SW versions below 4.5.
		56 - Downgrade below 4.5.4 is not supported for 802.11n devices with MAC addresses from pool BC:E6:7C:xx:xx:xx.
		57 - ACS/DCS is not supported in SW versions below 4.5.
		58 - MTU value above 1700 is not supported in SW versions below 4.6.
		59 - Downgrade below 4.6 is not supported for MIPS based boards.
		60 - 70/30 65/35 60/40 55/45 45/55 40/60 35/65 downlink/uplink ratios are not supported in SW versions below 4.6.
		61 - cnVision devices aren't supported in SW versions below 4.6.
		62 - Downgrade below 4.6.1 is not supported for Force 300-25 V2 board.
		63 - Downgrade below 4.7 is not supported for Force 200L.
		64 - Cannot downgrade below 4.6.1 if DL Max Rate is not set to Use AP's config.
		65 - DPI is not supported in SW versions below 4.7.
		66 - WLR Driver Mode is not supported in SW versions below 5.2.0.
		67 - Downgrade below 5.2 is not supported for 6GHz boards.
		68 - Intelbras or Mikrotik licenses activated. Versions below 4.7 don't support those.
		69 - Downgrade below 4.7 is not supported for boards with soft country lock set.
		70 - Downgrade below 5.4 is not supported for this type of devices.
		71 - Downgrade below 4.7 is not supported for boards with flexible mode selected.
		72 - Downgrade below 4.7 is not supported for boards with Port Forwarding configured containing ports 22(SSH), 161(SNMP), 80(HTTP), 443(HTTPS)
		73 - TR-069 option is not supported in SW versions below 5.2 on 802.11ax devices and 4.7 on other devices.
		74 - Downgrade below 4.6.4 is not supported for this device hardware.
		75 - Downgrade below 4.7.1 is not supported for Force 300-25L V2 board.
		77 - Downgrade below 4.7.1 is not supported with IPv6 mode selected other than Static or DHCP
		Device Allocation: AP, SM"
	::= { cambiumpmp80211SystemActions 13 }

cambiumpmp80211StatsPerSTAListUpdateStatus	OBJECT-TYPE
	SYNTAX	   Integer32 (0|1|2)
	MAX-ACCESS read-write
	STATUS	   current
	DESCRIPTION
		"Stats per SM List Update Status OID.
		 This OID is used to indicate Stats per SM list table status:
		 0 - No SMs are registerd to AP
		 1 - TBD
		 2 - TBD"
	::= { cambiumpmp80211SystemActions 14 }

cambiumpmp80211StatsPerSTAListUpdate  OBJECT-TYPE
	SYNTAX	   Integer32 (1)
	MAX-ACCESS read-write
	STATUS	   current
	DESCRIPTION
		"System OID for Stats per SM table update
		 When this OID is received,
		 Stats per SM table is getting updated with actual data"
	::= { cambiumpmp80211SystemActions 15 }

cambiumpmp80211STADisconnect OBJECT-TYPE
	SYNTAX	   Integer32 (1..120)
	MAX-ACCESS read-write
	STATUS	   current
	DESCRIPTION
		"System OID for particular SM disconnection
		Device Allocation: AP"
	::= { cambiumpmp80211SystemActions 16 }

cambiumpmp80211GPSAutopopulate OBJECT-TYPE
	SYNTAX	   Integer32 (1)
	MAX-ACCESS read-write
	STATUS	   current
	DESCRIPTION
		"System action to auto-populate GPS stats for device
		 into system configuration
		 device location for latitude, longitude and height
		Device Allocation: AP, SM"
	::= { cambiumpmp80211SystemActions 17 }

cambiumpmp80211SoftwareUpdateErrorStr  OBJECT-TYPE
	SYNTAX	   DisplayString (SIZE(1..128))
	MAX-ACCESS read-only
	STATUS	   current
	DESCRIPTION "Software Update error, text descriprion"
	::= { cambiumpmp80211SystemActions 18 }

cambiumpmp80211GpsFirmwareUpdate  OBJECT-TYPE
	SYNTAX	   OCTET STRING
	MAX-ACCESS read-write
	STATUS	   current
	DESCRIPTION
		"System OID for GPS Firmware Update Agent,
		Gps FW Update link value can be either remote firmware link (http, https, ftp),
		or local file link: /tmp/firmware.tar.gz
	NOTE: Device is automatically rebooted if link type is remote
		Device Allocation: AP, SM"
	::= { cambiumpmp80211SystemActions 19 }

cambiumpmp80211GpsFirmwareUpdateError  OBJECT-TYPE
	SYNTAX	   Integer32 (0..11)
	MAX-ACCESS read-only
	STATUS	   current
	DESCRIPTION
		"Firmware Update error code:
			0 - Finished successfully
			1 - SW update file download failed
			2 - Unpack failed, damaged or wrong format package, or file access error
			3 - GPS Firmware digital signature check failed
			4 - GPS DA digital signature check failed
			5 - GPS DA download to GPS device failed
			6 - GPS FW download to GPS device failed
			7 - Board SKU is not supported for this firmware
			8 - GPS general communication error
			9 - Opening binary sw-upgrader failed
			10 - General error of upgrade process
			11 - GPS Upgrade is Rejected because Trial Configuration is in progress
		Device Allocation: AP, SM"
	::= { cambiumpmp80211SystemActions 21 }

cambiumpmp80211GpsFirmwareUpdateErrorStr  OBJECT-TYPE
	SYNTAX	   DisplayString (SIZE(1..128))
	MAX-ACCESS read-only
	STATUS	   current
	DESCRIPTION "GPS Firmware Update error, text description"
	::= { cambiumpmp80211SystemActions 22 }

cambiumBridgeTableAPStatus	OBJECT-TYPE
	SYNTAX	   Integer32 (0|1|2)
	MAX-ACCESS read-write
	STATUS	   current
	DESCRIPTION
		"AP Bridge Table Update Status OID.
		This OID is used to indicate bridge table status:
			0 - Bridge table is empty
			1 - Bridge table is filled with data
			2 - AP Data is ready
		Device Allocation: AP"
	::= { cambiumpmp80211SystemActions 25 }

cambiumBridgeTableSTAUpdate	 OBJECT-TYPE
	SYNTAX	   Integer32 (1)
	MAX-ACCESS read-write
	STATUS	   current
	DESCRIPTION
		"System OID for AP Bridge Table update.
		 When this OID is received, bridge table is getting updated with actual
		 bridge table list
		 Device Allocation: SM"
	::= { cambiumpmp80211SystemActions 26 }

cambiumBridgeTableSTAStatus	 OBJECT-TYPE
	SYNTAX	   Integer32 (0|1|2)
	MAX-ACCESS read-write
	STATUS	   current
	DESCRIPTION
		"Bridge Table Update Status OID.
		This OID is used to indicate bridge table status:
			0 - Bridge table is empty
			1 - Bridge table is filled with data
			2 - SM Data is ready
		Device Allocation: SM"
	::= { cambiumpmp80211SystemActions 27 }

cambiumBridgeTableAPUpdate	OBJECT-TYPE
	SYNTAX	   Integer32 (1)
	MAX-ACCESS read-write
	STATUS	   current
	DESCRIPTION
		"System OID for Bridge Table update.
		 When this OID is received, bridge table is getting updated with actual
		 bridge table list
		 Device Allocation: AP"
	::= { cambiumpmp80211SystemActions 28 }

cambiumForceTabUpdDHCP	OBJECT-TYPE
	SYNTAX	   Integer32 (1)
	MAX-ACCESS read-write
	STATUS	   current
	DESCRIPTION
		"Force update DHCP Host table,
		1 - Force action
		Device Allocation: SM"
	::= { cambiumpmp80211SystemActions 30 }

cambiumForceTabUpdTrap	OBJECT-TYPE
	SYNTAX	   Integer32 (1)
	MAX-ACCESS read-write
	STATUS	   current
	DESCRIPTION
		"Force update SNMP Trap table,
		1 - Force action
		Device Allocation: AP, SM"
	::= { cambiumpmp80211SystemActions 31 }

cambiumForceTabUpdl2Frw	 OBJECT-TYPE
	SYNTAX	   Integer32 (1)
	MAX-ACCESS read-write
	STATUS	   current
	DESCRIPTION
		"Force update l2 Firewal table,
		1 - Force action
		Device Allocation: AP, SM"
	::= { cambiumpmp80211SystemActions 32 }

cambiumForceTabUpdl3Frw	 OBJECT-TYPE
	SYNTAX	   Integer32 (1)
	MAX-ACCESS read-write
	STATUS	   current
	DESCRIPTION
		"Force update l3 Firewal table,
		1 - Force action
		Device Allocation: AP, SM"
	::= { cambiumpmp80211SystemActions 33 }

cambiumForceTabUpdQos  OBJECT-TYPE
	SYNTAX	   Integer32 (1)
	MAX-ACCESS read-write
	STATUS	   current
	DESCRIPTION
		"Force update Quality of Service table,
		1 - Force action
		Device Allocation: AP, SM"
	::= { cambiumpmp80211SystemActions 34 }

cambiumForceTabUpdPortFw  OBJECT-TYPE
	SYNTAX	   Integer32 (1)
	MAX-ACCESS read-write
	STATUS	   current
	DESCRIPTION
		"Force update Port Forwarding table,
		1 - Force action
		Device Allocation: SM"
	::= { cambiumpmp80211SystemActions 35 }

cambiumForceTabUpdVlan	OBJECT-TYPE
	SYNTAX	   Integer32 (1)
	MAX-ACCESS read-write
	STATUS	   current
	DESCRIPTION
		"Force update Membership VLAN table,
		1 - Force action
		Device Allocation: SM"
	::= { cambiumpmp80211SystemActions 36 }

cambiumForceTabUpdMappingVlan OBJECT-TYPE
	SYNTAX	   Integer32 (1)
	MAX-ACCESS read-write
	STATUS	   current
	DESCRIPTION
		"Force update VLAN Mapping table,
				1 - Force action
		Device Allocation: AP, SM"
	::= { cambiumpmp80211SystemActions 37 }

cambiumConfigurationApplyOnReboot  OBJECT-TYPE
	SYNTAX	   Integer32 (1)
	MAX-ACCESS read-write
	STATUS	   current
	DESCRIPTION
		"OID for configuration Apply
		on stage of device reboot.
		Device Allocation: AP, SM"
	::= { cambiumpmp80211SystemActions 38 }

cambiumForceSTARescan OBJECT-TYPE
	SYNTAX	   Integer32 (1)
	MAX-ACCESS read-write
	STATUS	   current
	DESCRIPTION
		"force a STA rescan,
		1 - Force action
		Device Allocation: AP, SM"
	::= { cambiumpmp80211SystemActions 39 }

cambiumForceTabUpdMcastDeny OBJECT-TYPE
	SYNTAX	   Integer32 (1)
	MAX-ACCESS read-write
	STATUS	   current
	DESCRIPTION
		"Force update Multicast deny table,
		1 - Force action
		Device Allocation: AP, SM"
	::= { cambiumpmp80211SystemActions 40 }

cambiumForceTabUpdStaticRoutesCnf OBJECT-TYPE
	SYNTAX	   Integer32 (1)
	MAX-ACCESS read-write
	STATUS	   current
	DESCRIPTION
		"Force update Static Routes Conf table,
		1 - Force action
		Device Allocation: AP, SM"
	::= { cambiumpmp80211SystemActions 41 }

cambiumForceTabUpdMIR OBJECT-TYPE
	SYNTAX	   Integer32 (1)
	MAX-ACCESS read-write
	STATUS	   current
	DESCRIPTION
		"Force update MIR table,
		1 - Force action
		Device Allocation: AP, SM"
	::= { cambiumpmp80211SystemActions 42 }

cambiumForceTabUpdRadiusServ OBJECT-TYPE
	SYNTAX	   Integer32 (1)
	MAX-ACCESS read-write
	STATUS	   current
	DESCRIPTION
		"Force update Radius Server table,
		1 - Force action
		Device Allocation: AP, SM"
	::= { cambiumpmp80211SystemActions 43 }

cambiumForceTabUpdPrefAPList OBJECT-TYPE
	SYNTAX	   Integer32 (1)
	MAX-ACCESS read-write
	STATUS	   current
	DESCRIPTION
		"Force update Preferred AP list table,
		1 - Force action
		Device Allocation: AP, SM"
	::= { cambiumpmp80211SystemActions 44 }

cambiumForceTabUpdAPAlias OBJECT-TYPE
	SYNTAX	   Integer32 (1)
	MAX-ACCESS read-write
	STATUS	   current
	DESCRIPTION
		"Force update AP Alias table,
		1 - Force action
		Device Allocation: AP, SM"
	::= { cambiumpmp80211SystemActions 45 }

cambiumForceTabUpdPortFwSepMangIP  OBJECT-TYPE
	SYNTAX     Integer32 (1)
	MAX-ACCESS read-write
	STATUS     current
	DESCRIPTION
		"Force update Separate Management IP Port Forwarding table,
		1 - Force action
		Device Allocation: SM"
	::= { cambiumpmp80211SystemActions 46 }

cambiumAPListFlush OBJECT-TYPE
	SYNTAX	   Integer32 (1)
	MAX-ACCESS read-write
	STATUS	   current
	DESCRIPTION
		"Command stops scan and flush AP scan list,
		Related to cambiumSTAConnectedAPTable.
		1 - Force action
		Device Allocation: SM"
	::= { cambiumpmp80211SystemActions 47 }

cambiumCCTVListUpdate	 OBJECT-TYPE
	SYNTAX	   Integer32 (1)
	MAX-ACCESS read-write
	STATUS	   current
	DESCRIPTION
		"System OID for CCTV List update
		When this OID is received,
		Scanned CCTV list table is updated with actual CCTV scan list
		Device Allocation: SM"
	::= { cambiumpmp80211SystemActions 48 }

cambiumCCTVListUpdateStatus  OBJECT-TYPE
	SYNTAX	   Integer32 (0|1|2)
	MAX-ACCESS read-write
	STATUS	   current
	DESCRIPTION
		"CCTV List Update Status OID.
		This OID is used to indicate CCTV list table status:
			0 - No CCTVs are available in the list
			1 - CCTV List Table is getting updated
			2 - CCTV Data is ready
		Device Allocation: SM"
	::= { cambiumpmp80211SystemActions 49 }

cambiumCCTVListFlush OBJECT-TYPE
	SYNTAX	   Integer32 (1)
	MAX-ACCESS read-write
	STATUS	   current
	DESCRIPTION
		"Command flush CCTV scan list,
		Related to cambiumONVIFTable.
		1 - Force action
		Device Allocation: SM"
	::= { cambiumpmp80211SystemActions 50 }

cambiumForceTabUpdSwitch OBJECT-TYPE
	SYNTAX     Integer32 (1)
	MAX-ACCESS read-write
	STATUS     current
	DESCRIPTION
		"Force update for lanSwitchPortTable,
		1 - Force action
		Device Allocation: AP, SM"
	::= { cambiumpmp80211SystemActions 51 }

cambiumForceTabUpdDPIQoSApp OBJECT-TYPE
	SYNTAX	   Integer32 (1)
	MAX-ACCESS read-write
	STATUS	   current
	DESCRIPTION
		"Force update DPI QoS Application table,
		1 - Force action
		Device Allocation: AP, SM"
	::= { cambiumpmp80211SystemActions 52 }

cambiumpmp80211SoftwareUpdateStatusTrap NOTIFICATION-TYPE
	OBJECTS {
		cambiumpmp80211SoftwareUpdateError,
		cambiumpmp80211SoftwareUpdateErrorStr
	}
	STATUS	   current
	DESCRIPTION
		"Software Update error TRAP. Trap indicating Software Update State.
		This state is indicated by the included value of cambiumpmp80211GpsFirmwareUpdateError
		Device Allocation: AP, SM"
	::= { cambiumpmp80211SystemTraps 1 }

cambiumpmp80211GPSSyncStatusTrap NOTIFICATION-TYPE
	OBJECTS { cambiumToolbarGPSSyncStateStr }
	STATUS	   current
	DESCRIPTION
		"GPS Sync Status TRAP. Trap indicating GPS Sync State change.
		This state is indicated by the included value of cambiumToolbarGPSSyncState
		Device Allocation: AP, SM"
	::= { cambiumpmp80211SystemTraps 2 }

cambiumpmp80211SystemUpTrap NOTIFICATION-TYPE
	STATUS	   current
	DESCRIPTION
		"System UP TRAP. Trap indicating SNMP subSystem UP
		Device Allocation: AP, SM"
	::= { cambiumpmp80211SystemTraps 3 }

cambiumpmp80211DFSStatusTrap NOTIFICATION-TYPE
	OBJECTS { cambiumDFSStatus, cambiumDFSStatusStr }
	STATUS	   current
	DESCRIPTION
		"DFS Status TRAP. Trap indicating DFS Event.
		This event is indicated by the included value of cambiumDFSStatus
		Device Allocation: AP, SM"
	::= { cambiumpmp80211SystemTraps 4 }

cambiumpmp80211JSONCfgImportTrap NOTIFICATION-TYPE
	OBJECTS { cambiumJSONCfgImportError }
	STATUS	   current
	DESCRIPTION
		"JSON configuration import error trap. Trap catches JSON configuration
		import state. This state is indicated by the included value of
		cambiumJSONCfgImportError.
		Device Allocation: AP, SM"
	::= { cambiumpmp80211SystemTraps 5 }

cambiumpmp80211JSONCfgExportTrap NOTIFICATION-TYPE
	OBJECTS { cambiumJSONCfgExportError }
	STATUS	   current
	DESCRIPTION
		"JSON configuration export error trap. Trap catches JSON configuration
		export state. This state is indicated by the included value of
		cambiumJSONCfgExportError.
		Device Allocation: AP, SM"
	::= { cambiumpmp80211SystemTraps 6 }

cambiumpmp80211FullCfgRestoreTrap NOTIFICATION-TYPE
	OBJECTS { cambiumFullCfgRestoreError }
	STATUS	   current
	DESCRIPTION
		"Full configuration restore error trap. Trap catches full configuration
		restoring state. This state is indicated by the included value of
		cambiumFullCfgRestoreError.
		Device Allocation: AP, SM"
	::= { cambiumpmp80211SystemTraps 7 }

cambiumpmp80211FullCfgBackupTrap NOTIFICATION-TYPE
	OBJECTS { cambiumFullCfgBackUpError }
	STATUS	   current
	DESCRIPTION
		"Full configuration backup error trap. Trap catches full configuration
		backup state. This state is indicated by the included value of
		cambiumFullCfgBackUpError.
		Device Allocation: AP, SM"
	::= { cambiumpmp80211SystemTraps 8 }

cambiumpmp80211GpsFirmwareUpdateStatusTrap NOTIFICATION-TYPE
	OBJECTS {
		cambiumpmp80211GpsFirmwareUpdateError,
		cambiumpmp80211GpsFirmwareUpdateErrorStr
	}
	STATUS	   current
	DESCRIPTION
		"GPS Update error TRAP. Trap indicating GPS Firmware Update State.
		This state is indicated by the included value of cambiumpmp80211GpsFirmwareUpdateError
		Device Allocation: AP, SM"
	::= { cambiumpmp80211SystemTraps 9 }

cambiumpmp80211STADropTrap NOTIFICATION-TYPE
	OBJECTS { cambiumSTAMAC, cambiumSTADropReason }
	STATUS	   current
	DESCRIPTION
		"SM Drop trap. Trap catches dropped SM info. Information is
		contained in the included values of cambiumSTAMAC and
		cambiumSTADropReason.
		Device Allocation: AP"
	::= { cambiumpmp80211SystemTraps 10 }

cambiumpmp80211SMRegTrap NOTIFICATION-TYPE
	OBJECTS { cambiumSTAMAC }
	STATUS	   current
	DESCRIPTION
		"SM Registration trap. Trap catches registered SM info. Information is
		contained in the included value of cambiumSTAMAC.
		Device Allocation: AP"
	::= { cambiumpmp80211SystemTraps 11 }

cambiumpmp80211SystemRebootTrap NOTIFICATION-TYPE
	STATUS	   current
	DESCRIPTION
		"System reboot trap. Trap indicates that snmpd daemon is going to be shut
		down and the system is going to reboot.
		Device Allocation: AP, SM"
	::= { cambiumpmp80211SystemTraps 12 }

cambiumpmp80211SAModeTrap NOTIFICATION-TYPE
	STATUS	   current
	DESCRIPTION
		"Spectrum Analyzer mode trap. Trap indicates that the system is going to
		reboot in SA mode.
		Device Allocation: AP, SM"
	::= { cambiumpmp80211SystemTraps 13 }

cambiumpmpETSIframeSkipTrap NOTIFICATION-TYPE
	STATUS	   current
	DESCRIPTION
		"To much frame skipped due to CCA.
		Device Allocation: AP"
	::= { cambiumpmp80211SystemTraps 14 }

cambiumpmp80211NetworkEntryFailureTrap NOTIFICATION-TYPE
	OBJECTS { cambiumNetworkEntryFailureSTAMAC, cambiumNetworkEntryFailureReason }
	STATUS	   current
	DESCRIPTION
		"SM rejected trap. Trap obtains info about the latest rejected SM. Trap string
		is contained an information string with rejected reason and MAC of
		rejected SM. Trap message for a host is consisted of cambiumNetworkEntryFailureSTAMAC and
		cambiumNetworkEntryFailureReason objects.
		Device Allocation: AP"
	::= { cambiumpmp80211SystemTraps 15 }

cambiumpmp80211RFWatchdogTriggerTrap NOTIFICATION-TYPE
	STATUS	   current
	DESCRIPTION
		"RF Watchdog triggering event trap.
		Device Allocation: AP, SM"
	::= { cambiumpmp80211SystemTraps 16 }

cambiumLinkTestDuration	 OBJECT-TYPE
	SYNTAX	   Integer32 (2|4|6|8|10|12|14|16|18|20)
	MAX-ACCESS read-write
	STATUS	   current
	DESCRIPTION
		"Link Test Duration OID.
		Device Allocation: AP, SM"
	DEFVAL	{ 10 }
	::= { cambiumLinkTest 1 }

cambiumLinkTestPckSize	OBJECT-TYPE
	SYNTAX	   Integer32 (128|800|1500)
	MAX-ACCESS read-write
	STATUS	   current
	DESCRIPTION
		"Link Test Packet Size OID.
		Device Allocation: AP, SM"
	DEFVAL	{ 1500 }
	::= { cambiumLinkTest 2 }

cambiumLinkTestStartForMAC	OBJECT-TYPE
	SYNTAX	   DisplayString (SIZE(11..17))
	MAX-ACCESS read-write
	STATUS	   current
	DESCRIPTION
		"The Link Test Destination MAC address.
		Start Link Test by write this OID.
		Device Allocation: AP, SM"
	::= { cambiumLinkTest 3 }

cambiumLinkTestStatus  OBJECT-TYPE
	SYNTAX	   Integer32 (0..6)
	MAX-ACCESS read-only
	STATUS	   current
	DESCRIPTION
		"The Link Test Status OID.
		0: WAIT
		1: START
		2: BUSY
		3: SUCCESS
		4: SUCCESS (PREF PERIOD)
		5: ERROR UNREACHABLE
		6: ERROR FAIL
		Device Allocation: AP, SM"
	::= { cambiumLinkTest 4 }

cambiumLinkTestResultDate  OBJECT-TYPE
	SYNTAX	   DisplayString (SIZE(6..24))
	MAX-ACCESS read-only
	STATUS	   current
	DESCRIPTION
		"The Link Test Result Timestamp
		Device Allocation: AP, SM"
	::= { cambiumLinkTest 5 }

cambiumLinkTestResultUL	 OBJECT-TYPE
	SYNTAX	   Integer32 (0..1000000)
	MAX-ACCESS read-only
	STATUS	   current
	DESCRIPTION
		"Link Test Result Uplink.
		Device Allocation: AP, SM"
	DEFVAL	{ 0 }
	::= { cambiumLinkTest 6 }

cambiumLinkTestResultDL	 OBJECT-TYPE
	SYNTAX	   Integer32 (0..1000000)
	MAX-ACCESS read-only
	STATUS	   current
	DESCRIPTION
		"Link Test Result Downlink.
		Device Allocation: AP, SM"
	DEFVAL	{ 0 }
	::= { cambiumLinkTest 7 }

cambiumLinkTestForceAnt	OBJECT-TYPE
	SYNTAX	   Integer32 (0|1|2)
	MAX-ACCESS read-write
	STATUS	   current
	DESCRIPTION
		"Link Test Force Antenna OID.
			0: Auto
			1: Force Sector Antenna
			2: Force Smart Antenna
		Device Allocation: AP, SM"
	DEFVAL	{ 0 }
	::= { cambiumLinkTest 8 }

cambiumLinkTestMode  OBJECT-TYPE
	SYNTAX	   Integer32(1|2)
	MAX-ACCESS read-write
	STATUS	   current
	DESCRIPTION
		"Link Test Mode (PTP-550 only):
			1: Single Radio mode
			2: Channel Bonding mode
			3: MU-MIMO (Two Stations) mode
		Device Allocation: AP, SM"
	DEFVAL	{ 1 }
	::= { cambiumLinkTest 9 }

cambiumLinkTestMACs   OBJECT-TYPE
	SYNTAX	   OCTET STRING
	MAX-ACCESS read-write
	STATUS	   current
	DESCRIPTION
		"Link Test peer(s)' MAC(s).
		Device Allocation: AP, SM"
	::= { cambiumLinkTest 10 }

cambiumLinkTestStart  OBJECT-TYPE
	SYNTAX	   Integer32(1)
	MAX-ACCESS read-write
	STATUS	   current
	DESCRIPTION
		"Start Link Test. Assumes, that Link Test
		is already configured.
		Device Allocation: AP, SM"
	::= { cambiumLinkTest 20 }

caminfoScanFrequencyListCountry	 OBJECT-TYPE
	SYNTAX	   OCTET STRING (SIZE(0..128))
	MAX-ACCESS read-write
	STATUS	   current
	DESCRIPTION
		"Country for Frequency List 20/40 MHz band
		Device Allocation: AP, SM"
	::= { caminfo 1 }

caminfoScanFrequencyListTwentyBand	OBJECT-TYPE
	SYNTAX	   DisplayString (SIZE(0..1500))
	MAX-ACCESS read-only
	STATUS	   current
	DESCRIPTION
		"Scan Frequency List for 20 MHz band
		Device Allocation: SM"
	::= { caminfo 2 }

caminfoScanFrequencyListFortyBand  OBJECT-TYPE
	SYNTAX	   DisplayString (SIZE(0..1500))
	MAX-ACCESS read-only
	STATUS	   current
	DESCRIPTION
		"Scan Frequency List for 40 MHz band
		Device Allocation: SM"
	::= { caminfo 3 }

caminfoScanFrequencyListAllow59band	 OBJECT-TYPE
	SYNTAX	   Integer32 (0|1)
	MAX-ACCESS read-only
	STATUS	   current
	DESCRIPTION
		"Allow 59 band if the board is calibrated
		using new frequency values.
			0 - Do not Allow
			1 - Allow
		Device Allocation: AP, SM"
	::= { caminfo 4 }

caminfoScanFrequencyListAllow5and10bw  OBJECT-TYPE
	SYNTAX     Integer32 (0|1)
	MAX-ACCESS read-only
	STATUS     current
	DESCRIPTION
		"Does board chip allow operating on 5/10 MHz bandwidth.
			0 - Do not Allow
			1 - Allow
		Device Allocation: AP, SM"
	::= { caminfo 5 }

cambiumInternetConnectionServerIP OBJECT-TYPE
	SYNTAX	   IpAddress
	MAX-ACCESS read-write
	STATUS	   current
	DESCRIPTION
		"Internet Connection Server IP Address
		This is auxiliary IP address to ping
		in order to define Internet connection Status
		Device Allocation: AP, SM"
	::= { cambiumToolBarOpts 1 }

cambiumInternetConnectionPollPeriod OBJECT-TYPE
	SYNTAX	   Integer32 (1..3600)
	MAX-ACCESS read-write
	STATUS	   current
	DESCRIPTION
		"Internet Connection Server Ping period in seconds
		Device Allocation: AP, SM"
	::= { cambiumToolBarOpts 2 }

cambiumToolbarGlobeState OBJECT-TYPE
	SYNTAX	   Integer32 (0|1)
	MAX-ACCESS read-only
	STATUS	   current
	DESCRIPTION
		"Globe Internet Connectivity Status Icon State:
			0 - No Internet Connectivity,
			1 - Internet Connectivity
		Device Allocation: AP, SM"
	::= { cambiumToolBarStates 1 }

cambiumToolbarGPSSyncState OBJECT-TYPE
	SYNTAX	   Integer32 (0..5)
	MAX-ACCESS read-only
	STATUS	   current
	DESCRIPTION
		"GPS Current SYNC State:
			0 - The Initialization State
			1 - The No Synchronization State
			2 - The Synchronization State
			3 - The Hold Off State
			4 - The Regaining Sync State
			5 - The Free Run State
		Device Allocation: AP"
	::= { cambiumToolBarStates 2 }

cambiumToolbarDeviceConfigurationState	OBJECT-TYPE
	SYNTAX	   Integer32 (0..127)
	MAX-ACCESS read-only
	STATUS	   current
	DESCRIPTION
		"System configuration state OID.
		Bit masks:
			0000 0001 - System is configured.
			0000 0010 - There are unsaved changesets.
			0000 0100 - There are unrestarted services.
			0000 1000 - Needed reboot of the system.
			0001 0000 - Configurations was reset.
			0010 0000 - Services restarting in process.
			0100 0000 - Software Update performed.
		Device Allocation: AP, SM"
	::= { cambiumToolBarStates 3 }

cambiumToolbarSyncSource OBJECT-TYPE
	SYNTAX	   Integer32 (1|2|3|4|5)
	MAX-ACCESS read-only
	STATUS	   current
	DESCRIPTION
		"Sync Source Status:
			1 - GPS Sync Up,
			2 - GPS Sync Down,
			3 - CMM4 Sync,
			4 - CMM3 Sync,
			5 - CMM5 Sync (802.11ac)
		Device Allocation: AP"
	::= { cambiumToolBarStates 4 }

cambiumToolbarGPSSyncStateStr OBJECT-TYPE
	SYNTAX	   DisplayString (SIZE(0..128))
	MAX-ACCESS read-only
	STATUS	   current
	DESCRIPTION
		"GPS Current SYNC State (text)
		Device Allocation: AP"
	::= { cambiumToolBarStates 5 }

cambiumJSONCfgImport OBJECT-TYPE
	SYNTAX	   OCTET STRING (SIZE(0..128))
	MAX-ACCESS read-write
	STATUS	   current
	DESCRIPTION
		"OID to start import process, when valid link to JSON configuration file
		is received.
		Device Allocation: AP, SM"
	::= { cambiumCfg 1 }

cambiumJSONCfgImportStatus OBJECT-TYPE
	SYNTAX	   Integer32 (-1..3)
	MAX-ACCESS read-only
	STATUS	   current
	DESCRIPTION
		"OID to get the status of the import process:
		-1	Error
		 0	Idle
		 1	Downloading file
		 2	Importing file
		 3	Rebooting
		Device Allocation: AP, SM"
	::= { cambiumCfg 2 }

cambiumJSONCfgImportError OBJECT-TYPE
	SYNTAX	   DisplayString (SIZE(1..128))
	MAX-ACCESS read-only
	STATUS	   current
	DESCRIPTION
		"Import config Error message (text)
		Device Allocation: AP, SM"
	::= { cambiumCfg 3 }

cambiumJSONCfgImportMode OBJECT-TYPE
	SYNTAX	   Integer32 (0|1)
	MAX-ACCESS read-write
	STATUS	   current
	DESCRIPTION
		"OID to set mode of the following import process:
		 0	Normal mode (import all)
		 1	Import all but ignore illegal values
		Device Allocation: AP, SM"
	DEFVAL { 0 }
	::= { cambiumCfg 4 }

cambiumJSONCfgExport OBJECT-TYPE
	SYNTAX	   Integer32 (0|1)
	MAX-ACCESS read-write
	STATUS	   current
	DESCRIPTION
		"OID to start export process
		0	No action
		1	Start
		Device Allocation: AP, SM"
	::= { cambiumCfg 10 }

cambiumJSONCfgExportStatus OBJECT-TYPE
	SYNTAX	   Integer32 (-1..4)
	MAX-ACCESS read-only
	STATUS	   current
	DESCRIPTION
		"OID to get the status of the export process:
		-1	Error
		 0	Idle
		 1	Exporting JSON config
		 2	Moving config into upload directory
		 3	Preparing link for uploading
		 4	Success
		Device Allocation: AP, SM"
	::= { cambiumCfg 11 }

cambiumJSONCfgExportError OBJECT-TYPE
	SYNTAX	   DisplayString (SIZE(1..128))
	MAX-ACCESS read-only
	STATUS	   current
	DESCRIPTION
		"Export config Error message (text)
		Device Allocation: AP, SM"
	::= { cambiumCfg 12 }

cambiumJSONCfgExportLink OBJECT-TYPE
	SYNTAX	   DisplayString (SIZE(0..128))
	MAX-ACCESS read-only
	STATUS	   current
	DESCRIPTION
		"Link to the configuration file on the board.
		Only private community can read this attribute.
		Device Allocation: AP, SM"
	::= { cambiumCfg 13 }

cambiumFullCfgRestore OBJECT-TYPE
	SYNTAX	   OCTET STRING (SIZE(0..128))
	MAX-ACCESS read-write
	STATUS	   current
	DESCRIPTION
		"OID to start restore process, when valid link to full configuration
		file is received.
		Device Allocation: AP, SM"
	::= { cambiumCfg 20 }

cambiumFullCfgRestoreStatus OBJECT-TYPE
	SYNTAX	   Integer32 (-1..5)
	MAX-ACCESS read-only
	STATUS	   current
	DESCRIPTION
		"OID to get the status of the restore process:
		-1	Error
		 0	Idle
		 1	Downloading file
		 2	Decrypting
		 3	Unpacking
		 4	Importing
		 5	Rebooting
		Device Allocation: AP, SM"
	::= { cambiumCfg 21 }

cambiumFullCfgRestoreError OBJECT-TYPE
	SYNTAX	   DisplayString (SIZE(1..128))
	MAX-ACCESS read-only
	STATUS	   current
	DESCRIPTION
		"Restore config Error message (text)
		Device Allocation: AP, SM"
	::= { cambiumCfg 22 }

cambiumFullCfgRestoreMode OBJECT-TYPE
	SYNTAX	   Integer32 (0|1)
	MAX-ACCESS read-write
	STATUS	   current
	DESCRIPTION
		"OID to set mode of the following restore process:
		 0	Normal mode (restore all)
		 1	Restore all but ignore illegal values
		Device Allocation: AP, SM"
	DEFVAL { 0 }
	::= { cambiumCfg 23 }

cambiumFullCfgBackUp OBJECT-TYPE
	SYNTAX	   Integer32 (1..7)
	MAX-ACCESS read-write
	STATUS	   current
	DESCRIPTION
		"OID to start backup process
		Bitmask indicating which part of configuration to backup:
		001 - json-config files
		010 - files of security & certificates
		100 - log files
		Device Allocation: AP, SM"
	::= { cambiumCfg 30 }

cambiumFullCfgBackUpStatus OBJECT-TYPE
	SYNTAX	   Integer32 (-1..5)
	MAX-ACCESS read-only
	STATUS	   current
	DESCRIPTION
		"OID to get the status of the backup process:
		-1	Error
		 0	Idle
		 1	Packing configuration files
		 2	Encrypting configuration files
		 3	Moving packed files into upload directory
		 4	Preparing link for uploading
		 5	Success
		Device Allocation: AP, SM"
	::= { cambiumCfg 31 }

cambiumFullCfgBackUpError OBJECT-TYPE
	SYNTAX	   DisplayString (SIZE(1..128))
	MAX-ACCESS read-only
	STATUS	   current
	DESCRIPTION
		"Backup config Error message (text)
		Device Allocation: AP, SM"
	::= { cambiumCfg 32 }

cambiumFullCfgBackUpLink OBJECT-TYPE
	SYNTAX	   DisplayString
	MAX-ACCESS read-only
	STATUS	   current
	DESCRIPTION
		"Link to the packed configuration files on the board, ready to upload
		Device Allocation: AP, SM"
	::= { cambiumCfg 33 }

cambiumCfgTrialImport OBJECT-TYPE
	SYNTAX	   OCTET STRING (SIZE(0..128))
	MAX-ACCESS read-write
	STATUS	   current
	DESCRIPTION
		"Link to valid JSON configuration file to start a trial process
		Device Allocation: AP, SM"
	::= { cambiumCfg 40 }

cambiumCfgTrialStatus OBJECT-TYPE
	SYNTAX	   Integer32 (-1..3)
	MAX-ACCESS read-only
	STATUS	   current
	DESCRIPTION
		"OID to get the status of the configuration trial process:
		-1	Error
		 0	Idle
		 1	Downloading file
		 2	Importing file
		 3	Rebooting
		 4	Waiting for accept
		Device Allocation: AP, SM"
	::= { cambiumCfg 41 }

cambiumCfgTrialError OBJECT-TYPE
	SYNTAX	   DisplayString (SIZE(1..128))
	MAX-ACCESS read-only
	STATUS	   current
	DESCRIPTION
		"Configuration trial Error message (text)
		Device Allocation: AP, SM"
	::= { cambiumCfg 42 }

cambiumCfgTrialFinish OBJECT-TYPE
	SYNTAX	   Integer32 (0|1)
	MAX-ACCESS read-write
	STATUS	   current
	DESCRIPTION
		"OID to finish the configuration trial process:
		 0	Reject configuration being tried
		 1	Accept configuration being tried
		Device Allocation: AP, SM"
	::= { cambiumCfg 43 }

cambiumCfgTrialTimer OBJECT-TYPE
	SYNTAX	   Integer32 (0..3600)
	MAX-ACCESS read-only
	STATUS	   current
	DESCRIPTION
		"OID to get configuration trial timer. Value:
		 0			Not in Trial Configuration state
		 1..300		Time left before configuration trial is ended
		Device Allocation: AP, SM"
	::= { cambiumCfg 44 }

cambiumCfgTrialTimeout OBJECT-TYPE
	SYNTAX	   Integer32 (60..3600)
	MAX-ACCESS read-write
	STATUS	   current
	DESCRIPTION
		"Timeout for Configuration Trial before the configuration will be
		automatically rejected if not accepted otherwise.
		Device Allocation: AP, SM"
	DEFVAL	{ 300 }
	::= { cambiumCfg 45 }

acsEnable  OBJECT-TYPE
	SYNTAX	   Integer32 (0|1)
	MAX-ACCESS read-write
	STATUS	   current
	DESCRIPTION
		"Automatic Channel Selection (ACS) automatically selects best values for
		centerFrequency, dfsAlternative1CenterFrequency and dfsAlternative2CenterFrequency:
		 0 - Disable,
		 1 - Enable
		Device Allocation: AP"
	DEFVAL	{ 0 }
	::= { cambiumACSCfg 1 }

acsScanMinDwellTime	 OBJECT-TYPE
	SYNTAX	   Integer32 (50..500)
	MAX-ACCESS read-write
	STATUS	   current
	DESCRIPTION
		"Minimum dwell time during Automatic Channel Selection (ACS) scan in milliseconds.
		Device Allocation: AP"
	DEFVAL	{ 200 }
	::= { cambiumACSCfg 2 }

acsScanMaxDwellTime	 OBJECT-TYPE
	SYNTAX	   Integer32 (300..600)
	MAX-ACCESS read-write
	STATUS	   current
	DESCRIPTION
		"Maximum dwell time during Automatic Channel Selection (ACS) scan in milliseconds.
		Device Allocation: AP"
	DEFVAL	{ 300 }
	::= { cambiumACSCfg 3 }

acsControl	OBJECT-TYPE
	SYNTAX	   Integer32 (0..2)
	MAX-ACCESS read-write
	STATUS	   current
	DESCRIPTION
		"Automatic Channel Selection (ACS) control:
		 0 - No change,
		 1 - Run scan now,
		 2 - Abort current scan
		Device Allocation: AP"
	DEFVAL	{ 0 }
	::= { cambiumACSCfg 4 }

cambiumIDMMode OBJECT-TYPE
	SYNTAX	   Integer32 (0..1)
	MAX-ACCESS read-write
	STATUS	   current
	DESCRIPTION
		"OID to configure IDM Mode
		0 - System Wide
		1 - Local
		Device Allocation: AP, SM"
	::= { cambiumIDM 1 }

cambiumIDMTime OBJECT-TYPE
	SYNTAX	   Integer32 (1000..120000)
	MAX-ACCESS read-write
	STATUS	   current
	DESCRIPTION
		"OID to configure IDM Time.
		Device Allocation: AP, SM"
	::= { cambiumIDM 2 }

cambiumIDMEnable OBJECT-TYPE
	SYNTAX	   Integer32 (0|1)
	MAX-ACCESS read-write
	STATUS	   current
	DESCRIPTION
		"OID to enable/disable IDM feature
		0 - Disable IDM
		1 - Enable IDM
		Device Allocation: AP, SM"
	::= { cambiumIDM 3 }

dcsEnable OBJECT-TYPE
	SYNTAX     Integer32 (0|1|2)
	MAX-ACCESS read-write
	STATUS     current
	DESCRIPTION
		"Dynamic Channel Selection
		0 - Disable
		1 - Enable in DCS mode
		2 - Enable in ACS mode
		Device Allocation: AP"
	DEFVAL { 0 }
	::= { cambiumDCS 1 }

dcsLogFile  OBJECT-TYPE
	SYNTAX     DisplayString (SIZE(0|1..128))
	MAX-ACCESS read-only
	STATUS     current
	DESCRIPTION
		"File for DCS daemon log.
		Device Allocation: AP"
	::= { cambiumDCS 2 }

dcsFrequencyListFive  OBJECT-TYPE
	SYNTAX     DisplayString (SIZE(0|1..1500))
	MAX-ACCESS read-write
	STATUS     current
	DESCRIPTION
		"DCS Frequency List for 5 MHz
		Device Allocation: AP"
	::= { cambiumDCS 3 }

dcsFrequencyListTen  OBJECT-TYPE
	SYNTAX     DisplayString (SIZE(0|1..1500))
	MAX-ACCESS read-write
	STATUS     current
	DESCRIPTION
		"DCS Frequency List for 10 MHz
		Device Allocation: AP"
	::= { cambiumDCS 4 }

dcsFrequencyListTwenty  OBJECT-TYPE
	SYNTAX     DisplayString (SIZE(0|1..1500))
	MAX-ACCESS read-write
	STATUS     current
	DESCRIPTION
		"DCS Frequency List for 20 MHz
		Device Allocation: AP"
	::= { cambiumDCS 5 }

dcsFrequencyListForty  OBJECT-TYPE
	SYNTAX     DisplayString (SIZE(0|1..1500))
	MAX-ACCESS read-write
	STATUS     current
	DESCRIPTION
		"DCS Frequency List for 40 MHz
		Device Allocation: AP"
	::= { cambiumDCS 6 }

dcsFrequencyListEighty  OBJECT-TYPE
	SYNTAX     DisplayString (SIZE(0|1..1500))
	MAX-ACCESS read-write
	STATUS     current
	DESCRIPTION
		"DCS Frequency List for 80 MHz
		Device Allocation: AP"
	::= { cambiumDCS 7 }

dcsSwitchThreshold  OBJECT-TYPE
	SYNTAX     Integer32 (2..12)
	MAX-ACCESS read-write
	STATUS     current
	DESCRIPTION
		"An interferer level difference between
		the current channel and a candidate channel
		which is necessary for the channel switch.
		Value is measured in dBm.
		Device Allocation: AP"
	DEFVAL { 4 }
	::= { cambiumDCS 8 }

dcsSwitchMinHoldTime  OBJECT-TYPE
	SYNTAX     Integer32 (90..300)
	MAX-ACCESS read-write
	STATUS     current
	DESCRIPTION
		"Minimum time between channel switching.
		Value is measured in seconds.
		Device Allocation: AP"
	DEFVAL { 180 }
	::= { cambiumDCS 9 }

dcsThroughputDropThreshold  OBJECT-TYPE
	SYNTAX     Integer32 (10..40)
	MAX-ACCESS read-write
	STATUS     current
	DESCRIPTION
		"Throughput degradation which triggers channel
		switching.
		Value is measured in percents.
		Device Allocation: AP"
	DEFVAL { 20 }
	::= { cambiumDCS 10 }

dcsBandwidthMask OBJECT-TYPE
	SYNTAX     Integer32 (1..31)
	MAX-ACCESS read-write
	STATUS     current
	DESCRIPTION
		"Frequency Bandwidth as bitmask, fields are:
			1 - 20Mhz,
			2 - 40Mhz,
			4 - 10Mhz,
			8 - 5Mhz,
			16 - 80Mhz.
		Device Allocation: AP"
	DEFVAL	{ 1 }
	::= { cambiumDCS 11 }

cambiumGPSConfigResetTimeout OBJECT-TYPE
	SYNTAX     Integer32 (30..3600)
	MAX-ACCESS read-write
	STATUS     current
	DESCRIPTION
		"GPS Reset Timeout (in seconds).
		Allowed integers from 30 to 3600.
		Available only for devices with GPS-module.
		Device Allocation: AP"
	DEFVAL { 300 }
	::= { cambiumGPSConfig 4 }

cambiumIDMResultsTable OBJECT-TYPE
	SYNTAX	   SEQUENCE OF CambiumIDMResultsEntry
	MAX-ACCESS not-accessible
	STATUS	   current
	DESCRIPTION
		"This table contains information of IDM Results:
		  IDM Cycle,
		  Device MAC,
		  Last Comb RSSI,
		  Last Rate,
		  Max Rate,
		  Number of Packets,
		  CRC Comb RSSI,
		  CRC Ch0 RSSI,
		  CRC Ch1 RSSI,
		  CRC Number of Packets,
		  PRQ Comb RSSI,
		  PRQ Ch0 RSSI,
		  PRQ Ch1 RSSI,
		  PRQ Number of Packets,
		Device Allocation: AP, SM"
	::= { cambiumIDM 10 }

cambiumIDMResultsEntry OBJECT-TYPE
	SYNTAX	   CambiumIDMResultsEntry
	MAX-ACCESS not-accessible
	STATUS	   current
	DESCRIPTION
		"Wireless parameters mapping for particular device.
		Device Allocation: AP, SM"
	INDEX	{ cambiumAPNumberOfConnectedSTA }
	::= { cambiumIDMResultsTable 1 }

CambiumIDMResultsEntry ::= SEQUENCE {
	idmDeviceListCycle		  Integer32,
	idmDeviceListMAC		  DisplayString,
	idmDeviceListLCombRSSI	  Integer32,
	idmDeviceListLRate		  DisplayString,
	idmDeviceListMaxRate	  DisplayString,
	idmDeviceListPcktsNum	  Integer32,
	idmDeviceListCRCCombRSSI  Integer32,
	idmDeviceListCRCCh0RSSI	  Integer32,
	idmDeviceListCRCCh1RSSI	  Integer32,
	idmDeviceListCRCPcktsNum  Integer32,
	idmDeviceListPRQCombRSSI  Integer32,
	idmDeviceListPRQCh0RSSI	  Integer32,
	idmDeviceListPRQCh1RSSI	  Integer32,
	idmDeviceListPRQPcktsNum  Integer32
}

idmDeviceListCycle OBJECT-TYPE
	SYNTAX	   Integer32(1..1024)
	MAX-ACCESS read-only
	STATUS	   current
	DESCRIPTION
		"IDM Cycle Number.
		Device Allocation: AP, SM"
	::= { cambiumIDMResultsEntry 1 }

idmDeviceListMAC OBJECT-TYPE
	SYNTAX	   DisplayString (SIZE(11..17))
	MAX-ACCESS read-only
	STATUS	   current
	DESCRIPTION
		"MAC Address of device collected IDM Statistics.
		Device Allocation: AP, SM"
	::= { cambiumIDMResultsEntry 2 }

idmDeviceListLCombRSSI OBJECT-TYPE
	SYNTAX	   Integer32(-128..127)
	MAX-ACCESS read-only
	STATUS	   current
	DESCRIPTION
		"Combined RSSI of last received MPDU.
		Device Allocation: AP, SM"
	::= { cambiumIDMResultsEntry 3 }

idmDeviceListLRate OBJECT-TYPE
	SYNTAX	   DisplayString (SIZE(1..5))
	MAX-ACCESS read-only
	STATUS	   current
	DESCRIPTION
		"Rate code of last received MPDU.
		Device Allocation: AP, SM"
	::= { cambiumIDMResultsEntry 4 }

idmDeviceListMaxRate OBJECT-TYPE
	SYNTAX	   DisplayString (SIZE(1..5))
	MAX-ACCESS read-only
	STATUS	   current
	DESCRIPTION
		"Maximum rate code.
		Device Allocation: AP, SM"
	::= { cambiumIDMResultsEntry 5 }

idmDeviceListPcktsNum OBJECT-TYPE
	SYNTAX	   Integer32
	MAX-ACCESS read-only
	STATUS	   current
	DESCRIPTION
		"Number of packets filtered by IDM.
		Device Allocation: AP, SM"
	::= { cambiumIDMResultsEntry 6 }

idmDeviceListCRCCombRSSI OBJECT-TYPE
	SYNTAX	   Integer32(-128..127)
	MAX-ACCESS read-only
	STATUS	   current
	DESCRIPTION
		"Combined RSSI of maximum received CRC error MPDU.
		Device Allocation: AP, SM"
	::= { cambiumIDMResultsEntry 7 }

idmDeviceListCRCCh0RSSI OBJECT-TYPE
	SYNTAX	   Integer32(-128..127)
	MAX-ACCESS read-only
	STATUS	   current
	DESCRIPTION
		"Channel 0 RSSI of maximum received CRC error MPDU.
		Device Allocation: AP, SM"
	::= { cambiumIDMResultsEntry 8 }

idmDeviceListCRCCh1RSSI OBJECT-TYPE
	SYNTAX	   Integer32(-128..127)
	MAX-ACCESS read-only
	STATUS	   current
	DESCRIPTION
		"Channel 1 RSSI of maximum received CRC error MPDU.
		Device Allocation: AP, SM"
	::= { cambiumIDMResultsEntry 9 }

idmDeviceListCRCPcktsNum OBJECT-TYPE
	SYNTAX	   Integer32
	MAX-ACCESS read-only
	STATUS	   current
	DESCRIPTION
		"Number of packets with CRC error filtered by IDM.
		Device Allocation: AP, SM"
	::= { cambiumIDMResultsEntry 10 }

idmDeviceListPRQCombRSSI OBJECT-TYPE
	SYNTAX	   Integer32(-128..127)
	MAX-ACCESS read-only
	STATUS	   current
	DESCRIPTION
		"Combined RSSI of maximum received Probe Requests MPDU.
		Device Allocation: AP, SM"
	::= { cambiumIDMResultsEntry 11 }

idmDeviceListPRQCh0RSSI OBJECT-TYPE
	SYNTAX	   Integer32(-128..127)
	MAX-ACCESS read-only
	STATUS	   current
	DESCRIPTION
		"Channel 0 RSSI of maximum received Probe Requests MPDU.
		Device Allocation: AP, SM"
	::= { cambiumIDMResultsEntry 12 }

idmDeviceListPRQCh1RSSI OBJECT-TYPE
	SYNTAX	   Integer32(-128..127)
	MAX-ACCESS read-only
	STATUS	   current
	DESCRIPTION
		"Channel 1 RSSI of maximum received Probe Requests MPDU.
		Device Allocation: AP, SM"
	::= { cambiumIDMResultsEntry 13 }

idmDeviceListPRQPcktsNum OBJECT-TYPE
	SYNTAX	   Integer32
	MAX-ACCESS read-only
	STATUS	   current
	DESCRIPTION
		"Number of Probe Requests filtered by IDM.
		Device Allocation: AP, SM"
	::= { cambiumIDMResultsEntry 14 }

cambiumIDMSumMAC OBJECT-TYPE
	SYNTAX	   DisplayString (SIZE(11..17))
	MAX-ACCESS read-write
	STATUS	   current
	DESCRIPTION
		"MAC Address of device collected IDM Summary Statistics.
		Device Allocation: AP, SM"
	::= { cambiumIDM 11 }

cambiumIDMSumLCombRSSI OBJECT-TYPE
	SYNTAX	   Integer32(-128..127)
	MAX-ACCESS read-only
	STATUS	   current
	DESCRIPTION
		"Summary Combined RSSI of last received MPDU.
		Device Allocation: AP, SM"
	::= { cambiumIDM 12 }

cambiumIDMSumLRate OBJECT-TYPE
	SYNTAX	   DisplayString (SIZE(1..5))
	MAX-ACCESS read-only
	STATUS	   current
	DESCRIPTION
		"Summary Rate code of last received MPDU.
		Device Allocation: AP, SM"
	::= { cambiumIDM 13 }

cambiumIDMSumMaxRate OBJECT-TYPE
	SYNTAX	   DisplayString (SIZE(1..5))
	MAX-ACCESS read-only
	STATUS	   current
	DESCRIPTION
		"Summary Maximum rate code.
		Device Allocation: AP, SM"
	::= { cambiumIDM 14 }

cambiumIDMSumPcktsNum OBJECT-TYPE
	SYNTAX	   Integer32
	MAX-ACCESS read-only
	STATUS	   current
	DESCRIPTION
		"Summary Number of packets filtered by IDM.
		Device Allocation: AP, SM"
	::= { cambiumIDM 15 }

cambiumIDMSumCRCCombRSSI OBJECT-TYPE
	SYNTAX	   Integer32(-128..127)
	MAX-ACCESS read-only
	STATUS	   current
	DESCRIPTION
		"Summary Combined RSSI of maximum received CRC error MPDU.
		Device Allocation: AP, SM"
	::= { cambiumIDM 16 }

cambiumIDMSumCRCCh0RSSI OBJECT-TYPE
	SYNTAX	   Integer32(-128..127)
	MAX-ACCESS read-only
	STATUS	   current
	DESCRIPTION
		"Summary Channel 0 RSSI of maximum received CRC error MPDU.
		Device Allocation: AP, SM"
	::= { cambiumIDM 17 }

cambiumIDMSumCRCCh1RSSI OBJECT-TYPE
	SYNTAX	   Integer32(-128..127)
	MAX-ACCESS read-only
	STATUS	   current
	DESCRIPTION
		"Summary Channel 1 RSSI of maximum received CRC error MPDU.
		Device Allocation: AP, SM"
	::= { cambiumIDM 18 }

cambiumIDMSumCRCPcktsNum OBJECT-TYPE
	SYNTAX	   Integer32
	MAX-ACCESS read-only
	STATUS	   current
	DESCRIPTION
		"Summary Number of packets with CRC error filtered by IDM.
		Device Allocation: AP, SM"
	::= { cambiumIDM 19 }

cambiumIDMSumPRQCombRSSI OBJECT-TYPE
	SYNTAX	   Integer32(-128..127)
	MAX-ACCESS read-only
	STATUS	   current
	DESCRIPTION
		"Summary Combined RSSI of maximum received Probe Requests MPDU.
		Device Allocation: AP, SM"
	::= { cambiumIDM 20 }

cambiumIDMSumPRQCh0RSSI OBJECT-TYPE
	SYNTAX	   Integer32(-128..127)
	MAX-ACCESS read-only
	STATUS	   current
	DESCRIPTION
		"Summary Channel 0 RSSI of maximum received Probe Requests MPDU.
		Device Allocation: AP, SM"
	::= { cambiumIDM 21 }

cambiumIDMSumPRQCh1RSSI OBJECT-TYPE
	SYNTAX	   Integer32(-128..127)
	MAX-ACCESS read-only
	STATUS	   current
	DESCRIPTION
		"Summary Channel 1 RSSI of maximum received Probe Requests MPDU.
		Device Allocation: AP, SM"
	::= { cambiumIDM 22 }

cambiumIDMSumPRQPcktsNum OBJECT-TYPE
	SYNTAX	   Integer32
	MAX-ACCESS read-only
	STATUS	   current
	DESCRIPTION
		"Summary Number of Probe Requests filtered by IDM.
		Device Allocation: AP, SM"
	::= { cambiumIDM 23 }

cambiumIDMSummaryTable OBJECT-TYPE
	SYNTAX	   SEQUENCE OF CambiumIDMSummaryEntry
	MAX-ACCESS not-accessible
	STATUS	   current
	DESCRIPTION
		"This table contains information of IDM Summary Top Interferers:
		  Intrf MAC,
		  Intrf RSSI,
		  Intrf Ch0 RSSI,
		  Intrf Ch1 RSSI,
		  Intrf SSID,
		Device Allocation: AP, SM"
	::= { cambiumIDM 30 }

cambiumIDMSummaryEntry OBJECT-TYPE
	SYNTAX	   CambiumIDMSummaryEntry
	MAX-ACCESS not-accessible
	STATUS	   current
	DESCRIPTION
		"Wireless parameters mapping for particular device.
		Device Allocation: AP, SM"
	INDEX	{ cambiumAPNumberOfConnectedSTA }
	::= { cambiumIDMSummaryTable 1 }

CambiumIDMSummaryEntry ::= SEQUENCE {
	idmSummaryIntMAC	  DisplayString,
	idmSummaryIntCombRSSI Integer32,
	idmSummaryIntCh0RSSI  Integer32,
	idmSummaryIntCh1RSSI  Integer32,
	idmSummaryIntSSID	   DisplayString
}

idmSummaryIntMAC OBJECT-TYPE SYNTAX		DisplayString (SIZE(11..17))
	MAX-ACCESS read-only
	STATUS	   current
	DESCRIPTION
		"MAC Address of Interferer.
		Device Allocation: AP, SM"
	::= { cambiumIDMSummaryEntry 1 }

idmSummaryIntCombRSSI OBJECT-TYPE SYNTAX	 Integer32(-128..127)
	MAX-ACCESS read-only
	STATUS	   current
	DESCRIPTION
		"Interferer Combined RSSI.
		Device Allocation: AP, SM"
	::= { cambiumIDMSummaryEntry 2 }

idmSummaryIntCh0RSSI OBJECT-TYPE SYNTAX		Integer32(-128..127)
	MAX-ACCESS read-only
	STATUS	   current
	DESCRIPTION
		"Interferer Channel 0 RSSI.
		Device Allocation: AP, SM"
	::= { cambiumIDMSummaryEntry 3 }

idmSummaryIntCh1RSSI OBJECT-TYPE SYNTAX		Integer32(-128..127)
	MAX-ACCESS read-only
	STATUS	   current
	DESCRIPTION
		"Interferer Channel 1 RSSI.
		Device Allocation: AP, SM"
	::= { cambiumIDMSummaryEntry 4 }

idmSummaryIntSSID OBJECT-TYPE SYNTAX	 DisplayString (SIZE(0..32))
	MAX-ACCESS read-only
	STATUS	   current
	DESCRIPTION
		"SSID name of Interferer.
		Device Allocation: AP, SM"
	::= { cambiumIDMSummaryEntry 5 }

wirelessInterfaceAttemptScanFrequencyListFive	OBJECT-TYPE
	SYNTAX	   DisplayString (SIZE(0|1..1500))
	MAX-ACCESS read-write
	STATUS	   current
	DESCRIPTION
		"Scan Frequency List for 5MHz
		Invalid frequencies will be skipped on set attempt.
		Device Allocation: SM"
	::= { cambiumArcher 1 }

wirelessInterfaceAttemptScanFrequencyListTen	OBJECT-TYPE
	SYNTAX	   DisplayString (SIZE(0|1..1500))
	MAX-ACCESS read-write
	STATUS	   current
	DESCRIPTION
		"Scan Frequency List for 10MHz
		Invalid frequencies will be skipped on set attempt.
		Device Allocation: SM"
	::= { cambiumArcher 2 }

wirelessInterfaceAttemptScanFrequencyListTwenty	OBJECT-TYPE
	SYNTAX	   DisplayString (SIZE(0|1..1500))
	MAX-ACCESS read-write
	STATUS	   current
	DESCRIPTION
		"Scan Frequency List for 20MHz
		Invalid frequencies will be skipped on set attempt.
		Device Allocation: SM"
	::= { cambiumArcher 3 }

wirelessInterfaceAttemptScanFrequencyListForty	OBJECT-TYPE
	SYNTAX	   DisplayString (SIZE(0|1..1500))
	MAX-ACCESS read-write
	STATUS	   current
	DESCRIPTION
		"Scan Frequency List for 40MHz
		Invalid frequencies will be skipped on set attempt.
		Device Allocation: SM"
	::= { cambiumArcher 4 }

wirelessInterfaceAttemptScanFrequencyListEighty	OBJECT-TYPE
	SYNTAX	   DisplayString (SIZE(0|1..1500))
	MAX-ACCESS read-write
	STATUS	   current
	DESCRIPTION
		"Scan Frequency List for 80MHz
		Invalid frequencies will be skipped on set attempt.
		Device Allocation: SM"
	::= { cambiumArcher 5 }

wirelessInterfaceAttemptScanFrequencyList160M	OBJECT-TYPE
	SYNTAX	   DisplayString (SIZE(0|1..1500))
	MAX-ACCESS read-write
	STATUS	   current
	DESCRIPTION
		"Scan Frequency List for 160MHz
		Invalid frequencies will be skipped on set attempt.
		Device Allocation: SM"
	::= { cambiumArcher 6 }

wirelessInterfaceAttemptScanFrequencySkipCounter	OBJECT-TYPE
	SYNTAX	   Integer32
	MAX-ACCESS read-only
	STATUS	   current
	DESCRIPTION
		"Counter of skipped frequencies on setting attempt such as
		wirelessInterfaceAttemptScanFrequencyListFive
		Device Allocation: SM"
	::= { cambiumArcher 21 }

cambiumONVIFTable	OBJECT-TYPE
	SYNTAX      SEQUENCE OF CambiumONVIFEntry
	MAX-ACCESS  not-accessible
	STATUS      current
	DESCRIPTION
		"This table contains relevant information about ONVIF-cameras:
		Device Allocation: SM"
	::= { cambiumCCTVStatus 1 }

cambiumONVIFEntry OBJECT-TYPE
	SYNTAX      CambiumONVIFEntry
	MAX-ACCESS  not-accessible
	STATUS      current
	DESCRIPTION
		"Parameters mapping for particular ONVIF-camera.
		Device Allocation: SM"
	INDEX	{ cambiumONVIFMAC }
	::= { cambiumONVIFTable 1 }

CambiumONVIFEntry ::= SEQUENCE {
	cambiumONVIFIndex	Integer32,
	cambiumONVIFMAC		DisplayString,
	cambiumONVIFIP		IpAddress,
	cambiumONVIFHardware	DisplayString,
	cambiumONVIFName	DisplayString,
	cambiumONVIFLocation	DisplayString,
	cambiumONVIFProbeTime	Counter32,
	cambiumONVIFSTAMAC	DisplayString
}

cambiumONVIFIndex OBJECT-TYPE
	SYNTAX      Integer32
	MAX-ACCESS  read-only
	STATUS      current
	DESCRIPTION
		"Internal index of ONVIF-camera
		Device Allocation: SM"
	::= { cambiumONVIFEntry 1 }

cambiumONVIFMAC OBJECT-TYPE
	SYNTAX      DisplayString (SIZE(0|17))
	MAX-ACCESS  read-only
	STATUS      current
	DESCRIPTION
		"ONVIF-camera's MAC address
		Device Allocation: SM"
	::= { cambiumONVIFEntry 2 }

cambiumONVIFIP OBJECT-TYPE
	SYNTAX      IpAddress
	MAX-ACCESS  read-only
	STATUS      current
	DESCRIPTION
		"ONVIF-camera's IP address
		Device Allocation: SM"
	::= { cambiumONVIFEntry 3 }

cambiumONVIFHardware OBJECT-TYPE
	SYNTAX      DisplayString (SIZE(0|1..128))
	MAX-ACCESS  read-only
	STATUS      current
	DESCRIPTION
		"ONVIF-camera's model
		Device Allocation: SM"
	::= { cambiumONVIFEntry 4 }

cambiumONVIFName OBJECT-TYPE
	SYNTAX      DisplayString (SIZE(0|1..128))
	MAX-ACCESS  read-only
	STATUS      current
	DESCRIPTION
		"ONVIF-camera's manufacturer
		Device Allocation: SM"
	::= { cambiumONVIFEntry 5 }

cambiumONVIFLocation OBJECT-TYPE
	SYNTAX      DisplayString (SIZE(0|1..128))
	MAX-ACCESS  read-only
	STATUS      current
	DESCRIPTION
		"ONVIF-camera's location
		Device Allocation: SM"
	::= { cambiumONVIFEntry 6 }

cambiumONVIFProbeTime OBJECT-TYPE
	SYNTAX      Counter32
	MAX-ACCESS  read-only
	STATUS      current
	DESCRIPTION
		"Time of last ProbeMatch received from ONVIF-camera.
		Number of seconds since the Unix epoch (00:00:00 UTC on 1 January 1970).
		Device Allocation: SM"
	::= { cambiumONVIFEntry 7 }

cambiumONVIFSTAMAC OBJECT-TYPE
	SYNTAX      DisplayString (SIZE(0|17))
	MAX-ACCESS  read-only
	STATUS      current
	DESCRIPTION
		"STA MAC address
		Device Allocation: AP"
	::= { cambiumONVIFEntry 8 }

vmsagentEnable OBJECT-TYPE
	SYNTAX      Integer32 (0|1)
	MAX-ACCESS  read-write
	STATUS      current
	DESCRIPTION
		"VMS agent:
			0 - Disable
			1 - Enable
		Cambium provides VMS-agent (Video Management System).
		This allows a user to notify VMS about different events (associate, disconnect etc).
		This field enables this VMS-agent functionality.
		Device Allocation: SM"
	DEFVAL  { 1 }
	::= { vmsagent 1 }

vmsagentVMSType OBJECT-TYPE
	SYNTAX     Integer32 (1..10)
	MAX-ACCESS read-write
	STATUS     current
	DESCRIPTION
		"VMS's type.
		 1 - NxWitness
		 2 - Milestone
		 3 - Genetec
		 4 - Wisenet WAVE
		 5 - Avigilon
		 6 - AXIS
		 7 - DW Spectrum
		 8 - Digifort
		 9 - Siemens
		10 - Panasonic
		Device Allocation: SM"
	::= { vmsagent 2 }

vmsagentVMSAddr OBJECT-TYPE
	SYNTAX     OCTET STRING (SIZE(0..128))
	MAX-ACCESS read-write
	STATUS     current
	DESCRIPTION
		"VMS address:
		This specifies the VMS's FQDN or IP-address.
		Device Allocation: SM"
	::= { vmsagent 3 }

vmsagentVMSPort OBJECT-TYPE
	SYNTAX     Integer32 (1..65535)
	MAX-ACCESS read-write
	STATUS     current
	DESCRIPTION
		"VMS Port:
		This specifies the VMS's Port.
		Device Allocation: SM"
	::= { vmsagent 4 }

vmsagentUsername OBJECT-TYPE
	SYNTAX     DisplayString (SIZE(0..128))
	MAX-ACCESS read-write
	STATUS     current
	DESCRIPTION
		"Username for VMS.
		Device Allocation: SM"
	::= { vmsagent 5 }

vmsagentPassword OBJECT-TYPE
	SYNTAX     OCTET STRING (SIZE(0..128))
	MAX-ACCESS read-write
	STATUS     current
	DESCRIPTION
		"Password for VMS.
		Device Allocation: AP, SM"
	::= { vmsagent 6 }

cnvisionVMSPreviewHash OBJECT-TYPE
	SYNTAX     DisplayString (SIZE(0..128))
	MAX-ACCESS read-write
	STATUS     current
	DESCRIPTION
		"VMS Hash Code. Unique Hash,
		used for VMS Server GUI Preview Link generation
		Device Allocation: SM"
	::= { vmsagent 7 }

cambiumNSSAcceleratedConn OBJECT-TYPE
	SYNTAX     Integer32 (2048|4096|8192)
	MAX-ACCESS read-only
	STATUS     current
	DESCRIPTION
		"Total number of NSS accelerated connections.
		 Constantly selected with regard to HW.
		 Device Allocation: AP, SM"
	DEFVAL { 8192 }
	::= { cambiumNSS 1 }

cambiumNSSAcceleratedIPv4Conn OBJECT-TYPE
	SYNTAX     Integer32 (1024|2048|3072|4096|5120|6144|7168)
	MAX-ACCESS read-write
	STATUS     current
	DESCRIPTION
		"Number of NSS accelerated IPv4 connections.
		 Must be a multiple of 1024, and must be in the range
		 from 1024 to the total number of accelerated connections
		 minus 1024 inclusive. Affects the value for IPv6.
		 Device Allocation: AP, SM"
	DEFVAL { 7168 }
	::= { cambiumNSS 2 }

cambiumNSSAcceleratedIPv6Conn OBJECT-TYPE
	SYNTAX     Integer32 (1024|2048|3072|4096|5120|6144|7168)
	MAX-ACCESS read-only
	STATUS     current
	DESCRIPTION
		"Number of NSS accelerated IPv6 connections.
		 Automatically selected as the total number of
		 accelerated connections minus the number for IPv4.
		 Device Allocation: AP, SM"
	DEFVAL { 1024 }
	::= { cambiumNSS 3 }

cambiumNSSMcastFloodDestAth OBJECT-TYPE
	SYNTAX     Integer32 (-1..16)
	MAX-ACCESS read-write
	STATUS     current
	DESCRIPTION
		"Force NSS to forward mcast data to the selected ath port or flood
		-1: NSS will flood mcast data to all ports in bridge
		0..x: Use desired ath<n> port"
	DEFVAL { -1 }
	::= { cambiumNSS 4 }

cambiumNSSMcastFloodDestEth OBJECT-TYPE
	SYNTAX     Integer32 (-1..16)
	MAX-ACCESS read-write
	STATUS     current
	DESCRIPTION
		"Force NSS to forward mcast data to the selected eth port or flood
		-1: NSS will flood mcast data to all ports in bridge
		0..x: Use desired eth<n> port"
	DEFVAL { -1 }
	::= { cambiumNSS 5 }

dpiEnable OBJECT-TYPE
	SYNTAX      Integer32 (0|1)
	MAX-ACCESS  read-write
	STATUS      current
	DESCRIPTION
		"dpi agent:
			0 - Disable
			1 - Enable
		This field enables DPI functionality.
		Device Allocation: AP, SM"
	DEFVAL  { 1 }
	::= { dpi 1 }

dpiQoSEnable OBJECT-TYPE
	SYNTAX      Integer32 (0|1)
	MAX-ACCESS  read-write
	STATUS      current
	DESCRIPTION
		"dpi QoS module:
			0 - Disable
			1 - Enable
		This field enables DPI QoS functionality.
		Device Allocation: AP, SM"
	DEFVAL  { 1 }
	::= { dpi 2 }

dpiLogLevel OBJECT-TYPE
	SYNTAX      DisplayString (SIZE(0..16))
	MAX-ACCESS  read-write
	STATUS      current
	DESCRIPTION
		"DPI log levels:
			off - disable logging;
			error - log when error occurs;
			warn - log to make a warning;
			notice - normal but significant condition;
			info - normal information message;
			debug - printed in debug mode;
			trace - detailed messages;
			func - function call trace;
			all - Enable all log levels;
			system - use the highest level from syslogServerLogMask.
		In case non of these values is set, the logging level from
		syslogServerLogMask is going to be used.
		All log messages are printed to the kernel log.
		Device Allocation: AP, SM"
	DEFVAL  { "system" }
	::= { dpi 3 }

dpiLogComponents OBJECT-TYPE
	SYNTAX      DisplayString (SIZE(0..256))
	MAX-ACCESS  read-write
	STATUS      current
	DESCRIPTION
		"DPI log components:
			sys - system;
			mem - memory;
			pkt - packet;
			flow - flow;
			tcp - tcp;
			udp - udp;
			session - tcp session;
			tcp_pkt - trace tcp packet;
			udp_pkt - trace udp packet;
			icmp_pkt - trace icmp packet;
			other_pkt - trace other packet;
			mac - trace mac info;
			http - http;
			https - https;
			quic - quic;
			ftp - ftp;
			mail - mail;
			urinorm - http filter urinorm;
			apg - application guard;
			av - antivirus;
			dna - antivirus engine;
			decomp - decomp;
			wg - web guard;
			kf - keyword filter;
			pbf - port-based framework;
			insp - content inspection;
			copt - content option;
			hopt - header option;
			dm - device map;
			ts - tcp stream;
			dev - device table;
			uf - url filter;
			cmd - command;
			rde - rule-based detection engine;
			ips - intrusion-prevention system;
			psd - port-scan-defense system;
			qos - smart qos;
			event - event;
			mpp - metadata protocol parser;
			re3 - resoft3 module;
			tld - top level domain filtering;
			dns - dns cache module;
			sb - dns redirect module;
			rdpage - redirect page;
			all - enable all components;
			all_pkt - trace all packets.
		Specify all necessary components to enable logging. Use space as a separator.
		Device Allocation: AP, SM"
	DEFVAL  { "all" }
	::= { dpi 4 }


dpiQoSAppRulesTable  OBJECT-TYPE
	SYNTAX SEQUENCE OF DpiQoSAppRulesEntry
	MAX-ACCESS not-accessible
	STATUS	   current
	DESCRIPTION
		"dpi QoS Application rules table
		Device Allocation: AP, STA"
	::= { dpi 15 }

dpiQoSAppRulesEntry  OBJECT-TYPE
	SYNTAX	DpiQoSAppRulesEntry
	MAX-ACCESS not-accessible
	STATUS	   current
	DESCRIPTION
		"dpi QoS Application rules table entry
		Device Allocation: AP, STA"
	INDEX	{ dpiQoSAppRulesIndex }
	::= { dpiQoSAppRulesTable 1 }

DpiQoSAppRulesEntry ::= SEQUENCE {
	dpiQoSAppRulesIndex
		Integer32,
	dpiQoSAppID
		Integer32,
	dpiQoSAppPriority
		Integer32,
	dpiQoSAppRuleType
		Integer32
}

dpiQoSAppRulesIndex  OBJECT-TYPE
	SYNTAX	   Integer32 (0..64)
	MAX-ACCESS read-write
	STATUS	   current
	DESCRIPTION
		"dpi QoS rules table limiting number,
		Table Entry is cleared if Index is set to zero.
		Device Allocation: AP, STA"
	::= { dpiQoSAppRulesEntry 1 }

dpiQoSAppID  OBJECT-TYPE
	SYNTAX	   Integer32 (0..65535)
	MAX-ACCESS read-write
	STATUS	   current
	DESCRIPTION
		"dpi QoS application id or qos group id,
		look dpiQosAppRuleType
		Device Allocation: AP, STA"
	::= { dpiQoSAppRulesEntry 2 }

dpiQoSAppPriority  OBJECT-TYPE
	SYNTAX	   Integer32(1..3)
	MAX-ACCESS read-write
	STATUS	   current
	DESCRIPTION
		"dpi QoS application piority, using as qos mark:
		1 - Voice
		2 - High
		3 - Low
		Device Allocation: AP, STA"
	::= { dpiQoSAppRulesEntry 3 }

dpiQoSAppRuleType  OBJECT-TYPE
	SYNTAX	   Integer32(0..1)
	MAX-ACCESS read-write
	STATUS	   current
	DESCRIPTION
		"dpi QoS application rule type:
		0 - qos application group rule,
		1 - single application rule
		Device Allocation: AP, STA"
	::= { dpiQoSAppRulesEntry 4 }

cambiumTR069Enable OBJECT-TYPE
	SYNTAX      Integer32 (0|1)
	MAX-ACCESS  read-write
	STATUS      current
	DESCRIPTION
		"TR-069 Protocol Enable:
			0 - Disable
			1 - Enable
		TODO:
		Device Allocation: AP, SM"
	DEFVAL  { 0 }
	::= { tr069Local 1 }

cambiumTR069Interface OBJECT-TYPE
	SYNTAX     OCTET STRING (SIZE(0..128))
	MAX-ACCESS read-only
	STATUS     current
	DESCRIPTION
		"Interface for local HTTP-server (TR-069).
		Device Allocation: AP, SM"
	::= { tr069Local 2 }

cambiumTR069Port OBJECT-TYPE
	SYNTAX     Integer32 (1..65535)
	MAX-ACCESS read-only
	STATUS     current
	DESCRIPTION
		"Port for local HTTP-server (TR-069).
		Device Allocation: AP, SM"
	::= { tr069Local 3 }

cambiumTR069Username OBJECT-TYPE
	SYNTAX     DisplayString (SIZE(0..256))
	MAX-ACCESS read-only
	STATUS     current
	DESCRIPTION
		"Username for access local HTTP-server (TR-069).
		Device Allocation: AP, SM"
	::= { tr069Local 4 }

cambiumTR069Password OBJECT-TYPE
	SYNTAX     OCTET STRING (SIZE(0..256))
	MAX-ACCESS read-only
	STATUS     current
	DESCRIPTION
		"Password for access local HTTP-server (TR-069).
		Device Allocation: AP, SM"
	::= { tr069Local 5 }

cambiumTR069ACSURL OBJECT-TYPE
	SYNTAX     DisplayString (SIZE(0..256))
	MAX-ACCESS read-write
	STATUS     current
	DESCRIPTION
		"Auto Configuration Server's URL.
		Device Allocation: AP, SM"
	::= { tr069ACS 1 }

cambiumTR069ACSUsername OBJECT-TYPE
	SYNTAX     DisplayString (SIZE(0..256))
	MAX-ACCESS read-write
	STATUS     current
	DESCRIPTION
		"Username for access ACS.
		Device Allocation: AP, SM"
	::= { tr069ACS 2 }

cambiumTR069ACSPassword OBJECT-TYPE
	SYNTAX     OCTET STRING (SIZE(0..256))
	MAX-ACCESS read-write
	STATUS     current
	DESCRIPTION
		"Password for access ACS.
		Device Allocation: AP, SM"
	::= { tr069ACS 3 }

cambiumTR069Interval OBJECT-TYPE
	SYNTAX     Integer32
	MAX-ACCESS read-write
	STATUS     current
	DESCRIPTION
		"Interval for sending Inform message (TR-069).
		Device Allocation: AP, SM"
	::= { tr069ACS 4 }

reconnectPrimaryAPSelectIface	OBJECT IDENTIFIER ::= { cambiumpmp80211Tools 11 }

wirelessInterfaceReconnectPrimaryAPEnable OBJECT-TYPE
	SYNTAX     Integer32 (0|1)
	MAX-ACCESS read-write
	STATUS     current
	DESCRIPTION
		"Primary AP reconnect feature.
		If enabled, SM will periodically disconnect from secondary AP (if connected) and scan for primary AP.
		1 - feature enabled
		0 - feature disabled
		Device Allocation: SM"
	::= { reconnectPrimaryAPSelectIface 1 }

wirelessInterfaceReconnectPrimaryAPPeriod OBJECT-TYPE
	SYNTAX     Integer32 (5..720)
	MAX-ACCESS read-write
	STATUS     current
	DESCRIPTION
		"Period when AP will disconnect from secondary AP and try to connect to primary AP.
		Minimum allowed period - 5 minutes.
		Maximum - 720 minutes (12 hours).
		Device Allocation: SM"
	::= { reconnectPrimaryAPSelectIface 2 }

wirelessInterfaceReconnectPrimaryAPScanBG OBJECT-TYPE
	SYNTAX     Integer32 (0|1)
	MAX-ACCESS read-write
	STATUS     current
	DESCRIPTION
		"Primary AP reconnect background scan.
		Control for devices with two radio interfaces.
		If enabled, allows permanent scanning for primary AP without disconnecting from secondary.
		1 - background scan enabled
		0 - background scan disabled
		get returns always 0 for devices with one radio interface.
		Device Allocation: SM"
	::= { reconnectPrimaryAPSelectIface 3 }

wlrMUMIMOEnable OBJECT-TYPE
	SYNTAX		Integer32(0|1)
	MAX-ACCESS	read-write
	STATUS		current
	DESCRIPTION
		"Control parameter of MU-MIMO in WLR mode:
			0 - MU-MIMO is off
			1 - MU-MIMO is on
			Applicable for: AX devices in WLR mode
		Device Allocation: AP"
	DEFVAL { 0 }
	::= { wlr 1 }

END
