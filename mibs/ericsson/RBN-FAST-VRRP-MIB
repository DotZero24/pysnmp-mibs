-- *****************************************************************
-- RBN-FAST-VRRP-MIB    Redback Fast VRRP MIB
--
-- Copyright (c) 2008 Redback Networks, Inc.
-- All rights reserved.
--
-- *****************************************************************

RBN-FAST-VRRP-MIB DEFINITIONS ::= BEGIN

IMPORTS
    MODULE-IDENTITY,
    OBJECT-TYPE,
    NOTIFICATION-TYPE,
    Integer32
            FROM SNMPv2-SMI

    MODULE-COMPLIANCE,
    OBJECT-GROUP,
    NOTIFICATION-GROUP
            FROM SNMPv2-CONF

    ifIndex
            FROM IF-MIB

    VrId
            FROM VRRP-MIB

    rbnMgmt
            FROM RBN-SMI;

rbnFastVrrpMIB MODULE-IDENTITY
    LAST-UPDATED   "200805210000Z"    -- May 21, 2008
    ORGANIZATION   "Redback Networks, Inc."
    CONTACT-INFO
        "           Redback Networks, Inc.
            Postal: 300 Holger Way
                    San Jose, CA  95134
                    USA

             Phone: +1 408 750 5000
               Fax: +1 408 750 5599

            E-mail: mib-info@redback.com
            "
    DESCRIPTION
        "This MIB describes objects used for managing Redback Fast Virtual
         Router Redundancy Protocol (FVRRP) routers."
    REVISION "200805210000Z"    -- May 21, 2008
    DESCRIPTION
        " Initial Version."
    ::= { rbnMgmt 45 }

rbnFastVrrpMIBObjects    OBJECT IDENTIFIER ::= { rbnFastVrrpMIB 1 }
rbnFastVrrpConformance   OBJECT IDENTIFIER ::= { rbnFastVrrpMIB 2 }

--
-- Redback Fast VRRP objects
--
rbnFastVrrpOperTable OBJECT-TYPE
    SYNTAX      SEQUENCE OF RbnFastVrrpOperEntry
    MAX-ACCESS  not-accessible
    STATUS      current
    DESCRIPTION
        "A table contains rbnFastVrrpOperEntry entries"
    ::= { rbnFastVrrpMIBObjects 1 }

rbnFastVrrpOperEntry OBJECT-TYPE
    SYNTAX      RbnFastVrrpOperEntry
    MAX-ACCESS  not-accessible
    STATUS      current
    DESCRIPTION
        "Redback Fast VRRP operational characteristics entries"
    INDEX { ifIndex, rbnFastVrrpOperVrId }
    ::= { rbnFastVrrpOperTable 1 }

RbnFastVrrpOperEntry ::=
    SEQUENCE {
        rbnFastVrrpOperVrId                     VrId,
        rbnFastVrrpOperAdvertisementInterval    Integer32
    }

rbnFastVrrpOperVrId OBJECT-TYPE
     SYNTAX      VrId
     MAX-ACCESS  not-accessible
     STATUS      current
     DESCRIPTION
         "This object contains the Virtual Router Identifier (VRID) of
          Fast VRRP routers."
     ::= { rbnFastVrrpOperEntry 1 }

rbnFastVrrpOperAdvertisementInterval OBJECT-TYPE
    SYNTAX      Integer32 (100..999)
    UNITS       "milliseconds"
    MAX-ACCESS  read-only
    STATUS      current
    DESCRIPTION
        "The Fast VRRP advertisement messages time interval. This MIB object
         is used to replace the standard vrrpOperAdvertisementInterval(seconds)
         when Fast VRRP is enabled. Either vrrpOperAdvertisementInterval or
         rbnFastVrrpOperAdvertisementInterval is valid based on the VRRP
         configurations"
    ::= { rbnFastVrrpOperEntry 2 }

--
-- compliance statements
--

rbnFastVrrpMIBCompliances OBJECT IDENTIFIER ::= { rbnFastVrrpConformance 1 }
rbnFastVrrpMIBGroups      OBJECT IDENTIFIER ::= { rbnFastVrrpConformance 2 }

rbnFastVrrpCompliance MODULE-COMPLIANCE
    STATUS  current
    DESCRIPTION
        "The compliance statement for SNMP entities which implement
         the Redback Fast VRRP MIB."

    MODULE  -- this module
        MANDATORY-GROUPS {
            rbnFastVrrpObjectGroup
        }
    ::= { rbnFastVrrpMIBCompliances 1 }

--
-- groupings
--

rbnFastVrrpObjectGroup OBJECT-GROUP
    OBJECTS {
         rbnFastVrrpOperAdvertisementInterval
    }
    STATUS current
    DESCRIPTION
        "The collection of objects related to Fast VRRP objects."
    ::= { rbnFastVrrpMIBGroups 1 }

END
