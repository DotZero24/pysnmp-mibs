-- *****************************************************************
-- RBN-ATM2-MIB    Redback ATM2 MIB
--
-- Copyright (c) 2009 Redback Networks, Inc.
-- All rights reserved.
--
-- *****************************************************************

RBN-ATM2-MIB DEFINITIONS ::= BEGIN

IMPORTS
    MODULE-IDENTITY,
    OBJECT-TYPE,
    NOTIFICATION-TYPE,
    Counter32
            FROM SNMPv2-SMI

    MODULE-COMPLIANCE,
    OBJECT-GROUP
            FROM SNMPv2-CONF

    atmVplStatEntry,
    atmVclStatEntry,
    atmAal5VclStatEntry
            FROM ATM2-MIB

    rbnMgmt
            FROM RBN-SMI;

rbnAtm2MIB MODULE-IDENTITY
    LAST-UPDATED   "200906111700Z"    -- Jun 11, 2009
    ORGANIZATION   "Redback Networks, Inc."
    CONTACT-INFO
        "           Redback Networks, Inc.
            Postal: 300 Holger Way
                    San Jose, CA 95134
                    USA

             Phone: +1 408 750 5000
               Fax: +1 408 750 5599

            E-mail: mib-info@redback.com"
    DESCRIPTION
        "The MIB for instrumenting statistics associated with
        ATM VPL and VCL beyond those instrumented by ATM2-MIB."
    REVISION "200906111700Z"    -- Jun 11, 2009
    DESCRIPTION
        "Initial Version."
    ::= { rbnMgmt 50 }

rbnAtm2MIBObjects     OBJECT IDENTIFIER ::= { rbnAtm2MIB 1 }
rbnAtm2MIBConformance OBJECT IDENTIFIER ::= { rbnAtm2MIB 2 }

--
-- Redback ATM2 objects
--
rbnAtm2VplStatTable OBJECT-TYPE
    SYNTAX      SEQUENCE OF RbnAtm2VplStatEntry
    MAX-ACCESS  not-accessible
    STATUS      current
    DESCRIPTION
        "This table provides a collection of statistics
        objects of a VPL."
    ::= { rbnAtm2MIBObjects 1 }

rbnAtm2VplStatEntry OBJECT-TYPE
    SYNTAX      RbnAtm2VplStatEntry
    MAX-ACCESS  not-accessible
    STATUS      current
    DESCRIPTION
        "Each entry in this table represents a VPL."
    AUGMENTS { atmVplStatEntry }
    ::= { rbnAtm2VplStatTable 1 }

RbnAtm2VplStatEntry ::=
    SEQUENCE {
        rbnAtm2VplOutPktDrops Counter32
    }

rbnAtm2VplOutPktDrops OBJECT-TYPE
    SYNTAX      Counter32
    MAX-ACCESS  read-only
    STATUS      current
    DESCRIPTION
        "The number of transmit packets dropped by this VPL."
    ::= { rbnAtm2VplStatEntry 1 }

rbnAtm2VclStatTable OBJECT-TYPE
    SYNTAX      SEQUENCE OF RbnAtm2VclStatEntry
    MAX-ACCESS  not-accessible
    STATUS      current
    DESCRIPTION
        "This table provides a collection of statistics
        objects of a VCL."
    ::= { rbnAtm2MIBObjects 2 }

rbnAtm2VclStatEntry OBJECT-TYPE
    SYNTAX      RbnAtm2VclStatEntry
    MAX-ACCESS  not-accessible
    STATUS      current
    DESCRIPTION
        "Each entry in this table represents a VCL."
    AUGMENTS { atmVclStatEntry }
    ::= { rbnAtm2VclStatTable 1 }

RbnAtm2VclStatEntry ::=
    SEQUENCE {
        rbnAtm2VclOutPktDrops Counter32
    }

rbnAtm2VclOutPktDrops OBJECT-TYPE
    SYNTAX      Counter32
    MAX-ACCESS  read-only
    STATUS      current
    DESCRIPTION
        "The number of transmit packets dropped by this VCL."
    ::= { rbnAtm2VclStatEntry 1 }

rbnAtm2Aal5VclStatTable OBJECT-TYPE
    SYNTAX      SEQUENCE OF RbnAtm2Aal5VclStatEntry
    MAX-ACCESS  not-accessible
    STATUS      current
    DESCRIPTION
        "This table provides a collection of auxiliary
        objects providing AAL5 configuration and performance
        statistics of a VCL."
    ::= { rbnAtm2MIBObjects 3 }

rbnAtm2Aal5VclStatEntry OBJECT-TYPE
    SYNTAX      RbnAtm2Aal5VclStatEntry
    MAX-ACCESS  not-accessible
    STATUS      current
    DESCRIPTION
        "Each entry in this table represents a VCL."
    AUGMENTS { atmAal5VclStatEntry }
    ::= { rbnAtm2Aal5VclStatTable 1 }

RbnAtm2Aal5VclStatEntry ::=
    SEQUENCE {
        rbnAtm2Aal5VclOutPktDrops   Counter32
    }

rbnAtm2Aal5VclOutPktDrops OBJECT-TYPE
    SYNTAX      Counter32
    MAX-ACCESS  read-only
    STATUS      current
    DESCRIPTION
        "The number of AAL5 CPCS PDUs received for transmission
        on the AAL5 VCC at the interface identified by the
        ifIndex which were chosen to be dropped even though
        no errors had been detected to prevent their being
        transmitted.  One possible reason for dropping such a
        PDU could be a lack of available space on the interface
        output queue."
    ::= { rbnAtm2Aal5VclStatEntry 1 }

--
-- compliance statements
--
rbnAtm2MIBCompliances OBJECT IDENTIFIER ::= { rbnAtm2MIBConformance 1 }
rbnAtm2MIBGroups      OBJECT IDENTIFIER ::= { rbnAtm2MIBConformance 2 }

rbnAtm2Compliance MODULE-COMPLIANCE
    STATUS  current
    DESCRIPTION
        "The compliance statement for SNMP entities which implement
        the Redback ATM2 MIB."

    MODULE  -- this module
        MANDATORY-GROUPS {
            rbnAtm2CommonStatsGroup,
            rbnAtm2HostGroup
        }
    ::= { rbnAtm2MIBCompliances 1 }

--
-- groupings
--
rbnAtm2CommonStatsGroup OBJECT-GROUP
    OBJECTS {
       rbnAtm2VplOutPktDrops,
       rbnAtm2VclOutPktDrops
    }
    STATUS      current
    DESCRIPTION
        "A collection of objects providing supplemental
        VPL/VCL information beyond that supplied by
        IETF standards-track MIBs"
    ::= { rbnAtm2MIBGroups 1 }

rbnAtm2HostGroup OBJECT-GROUP
    OBJECTS {
       rbnAtm2Aal5VclOutPktDrops
    }
    STATUS      current
    DESCRIPTION
        "A collection of objects providing supplemental
        AAL5 VCL information beyond that supplied by
        IETF standards-track MIBs"
    ::= { rbnAtm2MIBGroups 2 }

END
