-- $Id: RBN-MEDIA-GATEWAY-MIB.my,v 1.1.18.1 2010/05/26 04:57:10 dazhao Exp $
-- $Source: /cvsroot/pkt/sw/se/xc/bsd/config/snmp/mibs/Attic/RBN-MEDIA-GATEWAY-MIB.my,v $
-- *****************************************************************
-- RBN-MEDIA-GATEWAY-MIB    MEDIA GATEWAY MIB
--
-- Copyright (c) 2009 Ericsson AB
-- All rights reserved.
--
-- *****************************************************************

RBN-MEDIA-GATEWAY-MIB DEFINITIONS ::= BEGIN

IMPORTS
    MODULE-IDENTITY,
    OBJECT-TYPE,
    NOTIFICATION-TYPE
            FROM SNMPv2-SMI

    DateAndTime
            FROM SNMPv2-TC

    SnmpAdminString
            FROM SNMP-FRAMEWORK-MIB

    IANAItuEventType,
    IANAItuProbableCause
                FROM IANA-ITU-ALARM-TC-MIB

    ItuPerceivedSeverity
                FROM ITU-ALARM-TC-MIB

    MODULE-COMPLIANCE,
    OBJECT-GROUP,
    NOTIFICATION-GROUP
            FROM SNMPv2-CONF
    rbnMgmt
            FROM RBN-SMI;

rbnMediaGatewayMib MODULE-IDENTITY
    LAST-UPDATED   "201004190000Z" -- April 19, 2010
    ORGANIZATION   "Ericsson Inc."
    CONTACT-INFO
            "       Ericsson Inc.
                    100 Headquarters Drive
                    San Jose, CA 95134
                    USA

             Phone: +1 408 750 5000
               Fax: +1 408 750 5599
            "

    DESCRIPTION
            "Defines the objects necessary to support the management of
            Media Gateway(MG) objects."

    REVISION      "201004190000Z" -- April 19, 2010
    DESCRIPTION
        "Modified the rbnH248LinkStatusAlarm Description regarding
        timeout value which triggers this notification"

    REVISION      "200909300000Z" -- September 30, 2009
    DESCRIPTION
        "Initial Version."

    ::= { rbnMgmt 52 }

rbnMediaGatewayNotifications OBJECT IDENTIFIER ::= { rbnMediaGatewayMib 0 }

rbnMediaGatewayObjects       OBJECT IDENTIFIER ::= { rbnMediaGatewayMib 1 }

rbnMediaGatewayConformance   OBJECT IDENTIFIER ::= { rbnMediaGatewayMib 2 }

--
-- some structure for the mib objects
--

rbnMediaGatewayNotify        OBJECT IDENTIFIER ::= { rbnMediaGatewayObjects 1 }

--
-- MEDIA GATEWAY notification objects
--

rbnMGEventDateAndTime OBJECT-TYPE
    SYNTAX      DateAndTime
    MAX-ACCESS  accessible-for-notify
    STATUS      current
    DESCRIPTION
        "The local date and time when the event was raised."
    ::= { rbnMediaGatewayNotify 1 }

rbnMGEventSeverity  OBJECT-TYPE
    SYNTAX      ItuPerceivedSeverity
    MAX-ACCESS  accessible-for-notify
    STATUS      current
    DESCRIPTION
        "The current severity of the event."
    ::= { rbnMediaGatewayNotify 2 }

rbnMGEventSender OBJECT-TYPE
    SYNTAX      SnmpAdminString  (SIZE(1..64))
    MAX-ACCESS  accessible-for-notify
    STATUS      current
    DESCRIPTION
        "Identifier of the entity sending the event."
    ::= { rbnMediaGatewayNotify 3 }

rbnMGEventType OBJECT-TYPE
    SYNTAX      IANAItuEventType
    MAX-ACCESS  accessible-for-notify
    STATUS      current
    DESCRIPTION
        "The type of the event."
    ::= { rbnMediaGatewayNotify 4 }

rbnMGEventProbableCause OBJECT-TYPE
    SYNTAX      IANAItuProbableCause
    MAX-ACCESS  accessible-for-notify
    STATUS      current
    DESCRIPTION
        "The probable cause for this event."
    ::= { rbnMediaGatewayNotify 5 }

rbnMGEventInformation OBJECT-TYPE
    SYNTAX      SnmpAdminString  (SIZE(0..256))
    MAX-ACCESS  accessible-for-notify
    STATUS      current
    DESCRIPTION
        "Additional information to describe the problem."
    ::= { rbnMediaGatewayNotify 6 }

--
-- NOTIFICATIONS - node for hanging notification definitions
--

rbnH248LinkStatusAlarm NOTIFICATION-TYPE
OBJECTS {
        rbnMGEventDateAndTime,
        rbnMGEventSeverity,
        rbnMGEventSender,
        rbnMGEventType,
        rbnMGEventProbableCause,
        rbnMGEventInformation
    }
    STATUS current
    DESCRIPTION
        "This notification signifies that the SNMP entity has detected that
        the H.248 link for a Media Gateway Controller (MGC) Group is down for
        more than configured timeout when rbnMGEventSeverity has the value 'major'.
        The timeout value is out of scope of the MIB module.
        The notification is sent with a value of 'clear' for
        rbnMGEventSeverity when the link state is restored (operationally up)
        or is obsoleted due to certain configuration change."
    ::= { rbnMediaGatewayNotifications 1 }

--
-- compliance statements
--
rbnMediaGatewayCompliances OBJECT IDENTIFIER ::= { rbnMediaGatewayConformance 1 }
rbnMediaGatewayGroups      OBJECT IDENTIFIER ::= { rbnMediaGatewayConformance 2 }

rbnMGCompliance MODULE-COMPLIANCE
    STATUS  current
    DESCRIPTION
        "The compliance statement for SNMP entities which implement
         the Media Gateway MIB."

    MODULE  -- this module
        MANDATORY-GROUPS {
            rbnMGNotifyObjectGroup,
            rbnMGLinkNotifyGroup
        }
    ::= { rbnMediaGatewayCompliances 1 }

--
-- groupings
--
rbnMGNotifyObjectGroup OBJECT-GROUP
    OBJECTS {
        rbnMGEventDateAndTime,
        rbnMGEventSeverity,
        rbnMGEventSender,
        rbnMGEventType,
        rbnMGEventProbableCause,
        rbnMGEventInformation
    }
    STATUS current
    DESCRIPTION
        "The collection of objects related to Media Gateway notifications."
    ::= { rbnMediaGatewayGroups 1 }

rbnMGLinkNotifyGroup NOTIFICATION-GROUP
    NOTIFICATIONS {
        rbnH248LinkStatusAlarm
    }
    STATUS current
    DESCRIPTION
        "Notification for tracking Media Gateway events."
    ::= { rbnMediaGatewayGroups 2 }
END
