-- *****************************************************************
-- RBN-PRODUCT-MIB	Enterprise Product and Entity Assignments
--
-- Copyright (c) 1999-2012 Ericsson AB.
-- All rights reserved.
--
-- *****************************************************************

RBN-PRODUCT-MIB DEFINITIONS ::= BEGIN

IMPORTS
	MODULE-IDENTITY,
	OBJECT-IDENTITY
		FROM SNMPv2-SMI
	rbnModules,
	rbnProducts,
	rbnEntities
		FROM RBN-SMI;

rbnProductMIB MODULE-IDENTITY
	LAST-UPDATED    "201203191800Z" -- Mar 19, 2012
      ORGANIZATION    "RedBack Networks, Inc."
	CONTACT-INFO
              "       RedBack Networks, Inc.

              Postal: 300 Holger Way
                      San Jose, CA  95134-1362
                        USA

                 Phone: +1 408 750 5000
                   Fax: +1 408 750 5599

              E-mail: mib-info@redback.com"
	DESCRIPTION
		"This management information module contains the
		administrative assignments which are used to
		uniquely identify physical components"


       REVISION        "201203191800Z" -- Mar 19, 2012
       DESCRIPTION
                "Added new OIDs:
                        rbnEntModuleSSR2Port40GEor100GE
                        rbnEntPortSSR40GEor100GE
                "

       REVISION        "201202101800Z" -- Feb 10, 2012
       DESCRIPTION
                "Added new OID:
                        rbnEntModuleSSC1
                "

       REVISION        "201106021800Z" -- June 02, 2011
       DESCRIPTION
                "Added new OID:
                        rbnEntPortSSRRPSWMgmt
                "

       REVISION        "201101191800Z" -- Jan 19, 2011
       DESCRIPTION
                "Update CONTACT-INFO & ORGANIZATION. Remove previous
                company name from descriptions."


       REVISION        "201010010000Z" -- Oct 01, 2010
       DESCRIPTION
                "Added new OIDs:
                        rbnEntCpuUnknown
                        rbnEntCpuOcteon
                        rbnEntModuleSEASE2
                        rbnSSR8020
                        rbnSSR8010
                        rbnSSR8006
                        rbnEntChassisSSR8020
                        rbnEntChassisSSR8010
                        rbnEntChassisSSR8006
                        rbnEntBackplaneSSR8020Data
                        rbnEntBackplaneSSR8010Data
                        rbnEntBackplaneSSR8006Data
                        rbnEntContainerSSR8020FanTray
                        rbnEntContainerSSR8020PowerModule
                        rbnEntContainerSSR8020Data
                        rbnEntContainerSSR8010FanTray
                        rbnEntContainerSSR8010PowerModule
                        rbnEntContainerSSR8010Data
                        rbnEntContainerSSR8006FanTray
                        rbnEntContainerSSR8006PowerModule
                        rbnEntContainerSSR8006Data
                        rbnEntFanTraySSR
                        rbnEntPowerModuleSSR
                        rbnEntModuleSSRALSW
                        rbnEntModuleSSRRPSW
                        rbnEntModuleSSRSW
                        rbnEntModuleSSR40Port1GE
                        rbnEntModuleSSR10Port10GE
                        rbnEntModuleSSR1Port100GE
                        rbnEntModuleSSR2Port40GE
                        rbnEntModuleSSR2or1Port40or100GE
                        rbnEntPortSSR1GE
                        rbnEntPortSSR10GE
                        rbnEntPortSSR100GE
                        rbnEntPortSSR40GE
                        rbnEntPortSSR40or100GE
                "

        REVISION        "201008270000Z" -- August 27, 2010
        DESCRIPTION
                "Added new OIDs:
                        rbnEntModuleSM8OR2PORTCHOC3OC12
                        rbnEntPortSMCHOC3OC12
                        rbnEntPortSMCHOC3
                "

        REVISION        "201004010000Z" -- April 01, 2010
        DESCRIPTION
                "Added new OIDs:
                        rbnEntModuleSEPos8xOC3
                        rbnEntModuleSEPos4xOC12
                        rbnEntModuleSEAtm2xOC12
                "

        REVISION        "201001270000Z" -- January 27, 2010
        DESCRIPTION
                "Added new OIDs:
                        rbnEntModuleSE1Port10GEOC192
                        rbnEntModuleSM1Port10GEOC192
                "
        REVISION        "200910050000Z" -- October 05, 2009
        DESCRIPTION
                "Added new OIDs:
                        rbnEntChassisSE1200H
                        rbnEntBackplaneSE1200HData
                        rbnEntContainerSE1200HData
                        rbnEntFanSE1200H
                "

        REVISION        "200909240000Z" -- September 24, 2009
        DESCRIPTION
                "Added new OIDs:
                        rbnEntModuleSE8OR2PORTCHOC3OC12
                        rbnEntPortSECHOC3OC12
                        rbnEntPortSECHOC3
                "

        REVISION        "200909130000Z" -- September 13, 2009
        DESCRIPTION
                "Added new OID:
                        rbnEntModuleSE10PortGIGEDDR2
                        rbnEntModuleSM10PortGIGEDDR2
                "

        REVISION        "200909100000Z" -- September 10, 2009
        DESCRIPTION
                "Added new OIDs:
                        rbnEntModuleSE4PortOC48
                        rbnEntModuleSE8PortOC3
                "

        REVISION        "200907160000Z" -- July 16, 2009
        DESCRIPTION
                "Added new OIDs:
                        rbnEntityTypeStack
                        rbnEntityTypeCPU
                        rbnEntityTypeMemory
                        rbnEntModuleSESSE
                        rbnEntityTypeDisk
                        rbnEntDiskSSE
                "

        REVISION        "200902040000Z" -- February 04, 2009
        DESCRIPTION
                "
                        rbnSmartEdge600
                        rbnSM240
                        rbnEntChassisSE600
                        rbnEntChassisSM240
                        rbnEntBackplaneSE600Data
                        rbnEntBackplaneSM240Data
                        rbnEntContainerSE600Data
                        rbnEntContainerSM240Data
                        rbnEntFanSE600
                        rbnEntFanSM240
                        rbnEntSensorAlarmSE600
                        rbnEntSensorAlarmSM240
                "

	REVISION        "200901200000Z" -- January 20, 2009
	DESCRIPTION
		"Added new OIDs:
			rbnEntModuleSMFE60GE2
                        rbnEntModuleSM20PortGIGE
                        rbnEntModuleSM4Port10GIGE
                        rbnEntPortSMEIM
                 Removed OID
                        rbnEntModuleSMRP1"

        REVISION        "200809230000Z" -- Sep, 23, 2008
        DESCRIPTION
                "Added new OIDs:
                	rbnEntPortSM10GIGEIM
			rbnEntPortSMRPMGMT
			rbnEntPortSMGIGEIM
			rbnEntPortSMGIGETM
			rbnEntPortSM10GIGETM"

        REVISION        "200807020000Z" -- July 02, 2008
        DESCRIPTION
                "Added new OIDs:
              		rbnEntModuleSE20PortGIGE
			rbnEntModuleSE4Port10GIGE
			rbnEntModuleSE10GIGETM
			rbnEntPortSE10GIGETM "

        REVISION        "200805200000Z" -- May 20, 2008
        DESCRIPTION
                "Added new OIDs:
			rbnSM480
			rbnEntChassisSM480
                        rbnEntBackplaneSM480Data
                        rbnEntContainerSM480Data
                        rbnEntFanSM480
			rbnEntModuleSM10GIGEIM
			rbnEntModuleSMRP2
			rbnEntModuleSMGIGEIM
			rbnEntModuleSMRP1
			rbnEntModuleSMGIGETM
			rbnEntModuleSM10GIGETM
                "
        REVISION        "200805080000Z" -- May 08, 2008
        DESCRIPTION
                "Added new OIDs:
                        rbnEntModuleSE5PortGIG
                "

        REVISION        "200709200000Z" -- September 20, 2007
        DESCRIPTION
                "Added new OIDs:
                        rbnEntModuleSEPOSOC192
                        rbnEntPortSEPOSOC192
                "

        REVISION        "200708080000Z" -- August 08, 2007
        DESCRIPTION
                "Added new OIDs:
                        rbnEntModuleSEFE60GE2
                "

	REVISION	"200705090000Z" -- May 09, 2007
	DESCRIPTION
		"Added new OIDs:
			rbnEntModuleSEASE
		"

        REVISION        "200702280000Z" -- February 28, 2007
        DESCRIPTION
                "Added new OIDs:
                        rbnEntModuleSEXC4
                        rbnEntPortSEXC4MGMT
                "

        REVISION        "200702140000Z" -- February 14, 2007
        DESCRIPTION
        	"Added new OIDs:
        		rbnSmartEdge1200
			rbnEntChassisSE1200
			rbnEntBackplaneSE1200Data
			rbnEntContainerSE1200Data
			rbnEntFanSE1200
                "

	REVISION	"200702050000Z" -- February 05, 2007
	DESCRIPTION
		"Added new OIDs:
			rbnEntModuleSE100AIMOC3MIC
			rbnEntPortSE100AIMOC3
		"
	REVISION        "200512270000Z" -- December 27, 2005
	DESCRIPTION
		"Added new OIDs:
			rbnSmartEdge100
			rbnEntChassisSE100
			rbnEntBackplaneSE100Data
			rbnEntContainerSE100Data
			rbnEntContainerSE100Carrier
			rbnEntModuleSE100XC
			rbnEntModuleSE100EMIC
			rbnEntModuleSE100FXMIC
			rbnEntModuleSE100GERJMIC
			rbnEntModuleSE100GEFXMIC
			rbnEntPortSE100XCMGMT
			rbnEntPortSE100EIM
			rbnEntPortSE100FXIM
			rbnEntPortSE100GERJIM
			rbnEntPortSE100GEFXIM
		"
	REVISION	"200503010000Z" -- March 1, 2005
	DESCRIPTION
		"Added new OIDs:
			rbnEntModuleSE10GIGEIM
			rbnEntPortSE10GIGEIM
		"
	REVISION	"200411050000Z" -- November 5, 2004
	DESCRIPTION
		"Added new OIDs:
			rbnEntModuleSEGIGETM
			rbnEntPortSEGIGETM
		"
	REVISION	"200405110000Z" -- May 11, 2004
	DESCRIPTION
		"Added new OIDs:
			rbnEntModuleSEAIMOC12E
			rbnEntPortSEAIMOC12E
		"
	REVISION	"200309250000Z" -- September 25, 2003
	DESCRIPTION
		"Added new OIDs:
			rbnEntModuleSEE3
			rbnEntPortSEE3
		"
	REVISION	"200307240000Z" -- July 24, 2003
	DESCRIPTION
		"Added new OIDs:
			rbnEntSensorAlarmSE400
		"
	REVISION	"200305191700Z" -- May 19, 2003
	DESCRIPTION
		"Added new OIDs:
			rbnEntModuleSMSXFE
		"
	REVISION	"200305050000Z" -- May 5,2003
	DESCRIPTION
		"Added new OID:
			rbnEntPortSEXC3MGMT
		"
	REVISION	"200303250000Z" -- March 25,2003
	DESCRIPTION
		"Added new OIDs:
			rbnSmartEdge400
			rbnEntChassisSE400
			rbnEntBackplaneSE400Data
			rbnEntContainerSE400Data
			rbnEntFanSE400
			rbnEntModuleSEXC3
		"
	REVISION	"200206130000Z" -- June 13, 2002
	DESCRIPTION
		"Added new OIDs:
			rbnEntModuleSECHSTM1E1
			rbnEntModuleSEE1
			rbnEntPortSECHSTM1E1
			rbnEntPortSEE1
		"
	REVISION	"200206060000Z" -- June 6, 2002
	DESCRIPTION
		"Updated the Contact Phone and Fax numbers.
		Added new OIDs:
			rbnEntModuleSEDS3
			rbnEntPortSEDS3
			rbnEntModuleSEAIMDS3
			rbnEntPortSEAIMDS3
		"
	REVISION	"200112120000Z" -- December 12, 2001
	DESCRIPTION
		"Changed the CONTACT-INFO postal address.
		Added new OIDs:
			rbnEntModuleSECHDS3
			rbnEntPortSECHDS3
		"
	REVISION	"200109261700Z" -- September 25, 2001
	DESCRIPTION
		"Added new OIDs:
			rbnEntModuleSEAIMOC3
			rbnEntModuleSEAIMOC12
			rbnEntPortSEAIMOC3
			rbnEntPortSEAIMOC12
		"
	REVISION	"200107251000Z" -- July 25, 2001
	DESCRIPTION
		"Added new OIDs:
			rbnEntModuleSECHOC12DS1
			rbnEntModuleSECHOC12DS3
			rbnEntPortSECHOC12DS1
			rbnEntPortSECHOC12DS3
		"
	REVISION	"200105151507Z" -- May 15, 2001
	DESCRIPTION
		"Updated name for new SMS platform.
		"
	REVISION	"200105041642Z" -- May 04, 2001
	DESCRIPTION
		"Added new OIDs:
			rbnEntChassisSE800
			rbnEntBackplaneSE800Data
			rbnEntContainerSE800Data
			rbnEntFanSE800
			rbnEntModuleSEXC
			rbnEntModuleSEEIM
			rbnEntModuleSEGIGEIM
			rbnEntModuleSEPOSOC12
			rbnEntModuleSEPOSOC48
			rbnEntModuleSEPOSOC3
			rbnEntPortSEXCMGMT
			rbnEntPortSEEIM
			rbnEntPortSEGIGEIM
			rbnEntPortSEPOSOC12
			rbnEntPortSEPOSOC48
			rbnEntPortSEPOSOC3
		"
	REVISION	"200102131857Z" -- February 13, 2001
	DESCRIPTION
		"Added new OID:
			rbnSmartEdge800
		"
	REVISION	"200102131007Z" -- February 13, 2001
	DESCRIPTION
		"Added support for new SMS platform.
		"
	REVISION	"200102011707Z" -- February 1, 2001
	DESCRIPTION
		"Added new OID:
		"
	REVISION	"200101051834Z" -- January 5, 2001
	DESCRIPTION
		"Added new OIDs:
		"
	REVISION	"200012281704Z" -- December 28, 2000
	DESCRIPTION
		"Added new OIDs:
		"
	REVISION	"200011151704Z" -- November 15, 2000
	DESCRIPTION
		"Added new OID:
			rbnEntBackplaneSMS10000Midplane
		"
	REVISION	"200011021454Z" -- November 2, 2000
	DESCRIPTION
		"Added new OID:
			rbnEntModuleSMSFE3
		"
	REVISION	"200010251523Z" -- October 25, 2000
	DESCRIPTION
		"Added new OIDs:
			rbnEntModuleSMSPIMCDS3
			rbnEntPortSMSPIMCDS3
		"
	REVISION	"200010201730Z" -- October 20, 2000
	DESCRIPTION
		"Added new OIDs:
			rbnEntModuleSMSFABRIC
			rbnEntModuleSMSTIMING
			rbnEntModuleSMSCM
			rbnEntModuleSMSSM
		"
	REVISION	"200009261330Z"	-- September 26, 2000
	DESCRIPTION
		"Added new OIDs:
		"
	REVISION	"200009251120Z"	-- Sep 25, 2000
	DESCRIPTION
		"Added new OID:
			rbnEntPortSMSAIME1
		"
	REVISION	"200007191544Z"	-- Jul 19, 2000
	DESCRIPTION
		"Added new OID:
			rbnEntModuleSMSAIME1
		"
	REVISION	"200007062150Z"	-- July 6, 2000
	DESCRIPTION
		"Added new OID:
		"
	REVISION	"200006161700Z"	-- Jun 16, 2000
	DESCRIPTION
		"In MODULE-IDENTITY, updated CONTACT-INFO and added
		new REVISION info.

		Added new OIDs:
		    rbnEntModuleSMSAIMOC12
		    rbnEntPortSMSAIMOC12"

	REVISION	"200006131700Z"	-- Jun 13, 2000
	DESCRIPTION
		"In MODULE-IDENTITY, updated CONTACT-INFO and added
		new REVISION info.

		Added new OIDs:
			rbnEntModuleSMSAIMT1
			rbnEntPortSMSAIMT1
			rbnEntModuleSMSAIME3
			rbnEntPortSMSAIME3"

	REVISION	"200005180000Z"	-- May 18, 2000
	DESCRIPTION
		"Addition of rbnSMS10000"

	REVISION	"9907081712Z"	-- Jul 8, 1999
	DESCRIPTION
		"Addition of rbnSMS1800"

	REVISION	"9808051900Z"	-- Aug 5, 1998
	DESCRIPTION
		"Initial version"
	::= { rbnModules 1 }


--
-- RedBack Product Assignments
--

rbnSMS1000 OBJECT-IDENTITY
	STATUS  current
	DESCRIPTION
		"The definitive identifier of the RedBack Networks
		SMS 1000"
	::= { rbnProducts 1 }

rbnSMS500 OBJECT-IDENTITY
	STATUS  current
	DESCRIPTION
		"The definitive identifier of the RedBack Networks
		SMS 500"
	::= { rbnProducts 2 }

rbnSMS1800 OBJECT-IDENTITY
        STATUS  current
        DESCRIPTION
                "The definitive identifier of the RedBack Networks
                SMS 1800"
        ::= { rbnProducts 3 }

rbnSMS10000 OBJECT-IDENTITY
        STATUS  current
        DESCRIPTION
                "The definitive identifier of the RedBack Networks
                SMS 10000"
        ::= { rbnProducts 4 }







rbnSmartEdge800 OBJECT-IDENTITY
        STATUS  current
        DESCRIPTION
                "The definitive identifier of the RedBack Networks
                SmartEdge 800"
        ::= { rbnProducts 10 }

rbnSmartEdge400 OBJECT-IDENTITY
        STATUS  current
        DESCRIPTION
                "The definitive identifier of the RedBack Networks
                SmartEdge 400"
        ::= { rbnProducts 11 }

rbnSmartEdge100 OBJECT-IDENTITY
        STATUS  current
        DESCRIPTION
                "The definitive identifier of the RedBack Networks
                SmartEdge 100"
        ::= { rbnProducts 12 }

rbnSmartEdge1200 OBJECT-IDENTITY
        STATUS  current
        DESCRIPTION
                "The definitive identifier of the RedBack Networks
                SmartEdge 1200"
        ::= { rbnProducts 13 }

rbnSM480 OBJECT-IDENTITY
        STATUS  current
        DESCRIPTION
                "The definitive identifier of the RedBack Networks
                SM 480"
        ::= { rbnProducts 14 }

rbnSmartEdge600 OBJECT-IDENTITY
        STATUS  current
        DESCRIPTION
                "The definitive identifier of the RedBack Networks
                SmartEdge 600"
        ::= { rbnProducts 15 }

rbnSM240 OBJECT-IDENTITY
        STATUS  current
        DESCRIPTION
                "The definitive identifier of the RedBack Networks
                SM240"
        ::= { rbnProducts 16 }

rbnSSR8020 OBJECT-IDENTITY
        STATUS  current
        DESCRIPTION
                "The definitive identifier for the Smart Services
                Router(SSR) 8020"
        ::= { rbnProducts 17 }

rbnSSR8010 OBJECT-IDENTITY
        STATUS  current
        DESCRIPTION
                "The definitive identifier for the Smart Services
                Router(SSR) 8010"
        ::= { rbnProducts 18 }

rbnSSR8006 OBJECT-IDENTITY
        STATUS  current
        DESCRIPTION
                "The definitive identifier for the Smart Services
                Router(SSR) 8006"
        ::= { rbnProducts 19 }


--
-- RedBack Entity Assignments
--
-- { rbnEntities 1 } and { rbnEntities 2 } are unassigned

rbnEntityTypeOther OBJECT-IDENTITY
      STATUS  current
      DESCRIPTION
              "The top-level category identifier for entities which
              reside in the ENTITY-MIB PhysicalClass *other*"
      ::= { rbnEntities 1 }

rbnEntityTypeUnknown OBJECT-IDENTITY
      STATUS  current
      DESCRIPTION
              "The top-level category identifier for entities which
              reside in the ENTITY-MIB PhysicalClass *unknown*"
      ::= { rbnEntities 2 }

rbnEntityTypeChassis OBJECT-IDENTITY
      STATUS  current
      DESCRIPTION
              "The top-level category identifier for entities which
              reside in the ENTITY-MIB PhysicalClass *chassis*"
      ::= { rbnEntities 3 }

rbnEntChassisSMS1000 OBJECT-IDENTITY
      STATUS  current
      DESCRIPTION
              "The definitive identifier for the RedBack Networks
              SMS 1000 chassis entity."
      ::= { rbnEntityTypeChassis 1 }

rbnEntChassisSMS500 OBJECT-IDENTITY
      STATUS  current
      DESCRIPTION
              "The definitive identifier for the RedBack Networks
              SMS 500 chassis entity."
      ::= { rbnEntityTypeChassis 2 }

rbnEntChassisSMS1800 OBJECT-IDENTITY
      STATUS  current
      DESCRIPTION
              "The definitive identifier for the RedBack Networks
              SMS 1800 chassis entity."
      ::= { rbnEntityTypeChassis 3 }

rbnEntChassisSMS10000 OBJECT-IDENTITY
      STATUS  current
      DESCRIPTION
              "The definitive identifier for the RedBack Networks
              SMS 10000 chassis entity."
      ::= { rbnEntityTypeChassis 4 }


rbnEntChassisSE800 OBJECT-IDENTITY
      STATUS current
      DESCRIPTION
              "The definitive identifier for the Redback Networks
              SE 800 chassis entity."
      ::= { rbnEntityTypeChassis 6 }

rbnEntChassisSE400 OBJECT-IDENTITY
      STATUS current
      DESCRIPTION
              "The definitive identifier for the Redback Networks
              SE 400 chassis entity."
      ::= { rbnEntityTypeChassis 7 }

rbnEntChassisSE100 OBJECT-IDENTITY
      STATUS current
      DESCRIPTION
              "The definitive identifier for the Redback Networks
              SE 100 chassis entity."
      ::= { rbnEntityTypeChassis 8 }

rbnEntChassisSE1200 OBJECT-IDENTITY
      STATUS current
      DESCRIPTION
              "The definitive identifier for the Redback Networks
              SE 1200 chassis entity."
      ::= { rbnEntityTypeChassis 9 }

rbnEntChassisSM480 OBJECT-IDENTITY
      STATUS current
      DESCRIPTION
              "The definitive identifier for the Redback Networks
              SM 480 chassis entity."
      ::= { rbnEntityTypeChassis 10 }


rbnEntChassisSE600 OBJECT-IDENTITY
      STATUS current
      DESCRIPTION
              "The definitive identifier for the Redback Networks
              SmartEdge 600 chassis entity."
      ::= { rbnEntityTypeChassis 11 }

rbnEntChassisSM240 OBJECT-IDENTITY
      STATUS current
      DESCRIPTION
              "The definitive identifier for the Redback Networks
              SM240 chassis entity."
      ::= { rbnEntityTypeChassis 12 }

rbnEntChassisSE1200H OBJECT-IDENTITY
      STATUS current
      DESCRIPTION
              "The definitive identifier for the SE1200H chassis entity."
      ::= { rbnEntityTypeChassis 13 }

rbnEntChassisSSR8020 OBJECT-IDENTITY
      STATUS current
      DESCRIPTION
              "The definitive identifier for the Smart Services Router 8020
              chassis entity."
      ::= { rbnEntityTypeChassis 14 }

rbnEntChassisSSR8010 OBJECT-IDENTITY
      STATUS current
      DESCRIPTION
              "The definitive identifier for the Smart Services Router 8010
              chassis entity."
      ::= { rbnEntityTypeChassis 15 }

rbnEntChassisSSR8006 OBJECT-IDENTITY
      STATUS current
      DESCRIPTION
              "The definitive identifier for the Smart Services Router 8006
              chassis entity."
      ::= { rbnEntityTypeChassis 16 }

rbnEntityTypeBackplane OBJECT-IDENTITY
      STATUS  current
      DESCRIPTION
              "The top-level category identifier for entities which
              reside in the ENTITY-MIB PhysicalClass *backplane*"
      ::= { rbnEntities 4 }

rbnEntBackplaneSMS1000Data OBJECT-IDENTITY
      STATUS  current
      DESCRIPTION
              "The definitive identifier for the RedBack Networks
              SMS 1000 data backplane entity."
      ::= { rbnEntityTypeBackplane 1 }

rbnEntBackplaneSMS1000Power OBJECT-IDENTITY
      STATUS  current
      DESCRIPTION
              "The definitive identifier for the RedBack Networks
              SMS 1000 power backplane entity."
      ::= { rbnEntityTypeBackplane 2 }

rbnEntBackplaneSMS500Data OBJECT-IDENTITY
      STATUS  current
      DESCRIPTION
              "The definitive identifier for the RedBack Networks
              SMS 500 data backplane entity."
      ::= { rbnEntityTypeBackplane 3 }

rbnEntBackplaneSMS500Power OBJECT-IDENTITY
      STATUS  current
      DESCRIPTION
              "The definitive identifier for the RedBack Networks
              SMS 500 power backplane entity."
      ::= { rbnEntityTypeBackplane 4 }

rbnEntBackplaneSMS1800Data OBJECT-IDENTITY
      STATUS  current
      DESCRIPTION
              "The definitive identifier for the RedBack Networks
              SMS 1800 data backplane entity."
      ::= { rbnEntityTypeBackplane 5 }

rbnEntBackplaneSMS1800Power OBJECT-IDENTITY
      STATUS  current
      DESCRIPTION
              "The definitive identifier for the RedBack Networks
              SMS 1800 power backplane entity."
      ::= { rbnEntityTypeBackplane 6 }

rbnEntBackplaneSMS10000Midplane OBJECT-IDENTITY
      STATUS  current
      DESCRIPTION
              "The definitive identifier for the RedBack Networks
              SMS 10000 midplane entity."
      ::= { rbnEntityTypeBackplane 7 }



rbnEntBackplaneSE800Data OBJECT-IDENTITY
      STATUS current
      DESCRIPTION
              "The definitive identifier for the Redback Networks
              SE 800 data backplane entity."
      ::= { rbnEntityTypeBackplane 10 }

rbnEntBackplaneSE400Data OBJECT-IDENTITY
      STATUS current
      DESCRIPTION
              "The definitive identifier for the Redback Networks
              SE 400 data backplane entity."
      ::= { rbnEntityTypeBackplane 11 }

rbnEntBackplaneSE100Data OBJECT-IDENTITY
      STATUS current
      DESCRIPTION
              "The definitive identifier for the Redback Networks
              SE 100 data backplane entity."
      ::= { rbnEntityTypeBackplane 12 }

rbnEntBackplaneSE1200Data OBJECT-IDENTITY
      STATUS current
      DESCRIPTION
              "The definitive identifier for the Redback Networks
              SE 1200 data backplane entity."
      ::= { rbnEntityTypeBackplane 13 }

rbnEntBackplaneSM480Data OBJECT-IDENTITY
      STATUS current
      DESCRIPTION
              "The definitive identifier for the Redback Networks
              SM 480 data backplane entity."
      ::= { rbnEntityTypeBackplane 14 }


rbnEntBackplaneSE600Data OBJECT-IDENTITY
      STATUS current
      DESCRIPTION
              "The definitive identifier for the Redback Networks
              SmartEdge 600 data backplane entity."
      ::= { rbnEntityTypeBackplane 15 }

rbnEntBackplaneSM240Data OBJECT-IDENTITY
      STATUS current
      DESCRIPTION
              "The definitive identifier for the Redback Networks
              SM240 data backplane entity."
      ::= { rbnEntityTypeBackplane 16 }

rbnEntBackplaneSE1200HData OBJECT-IDENTITY
      STATUS current
      DESCRIPTION
              "The definitive identifier for the SE1200H data backplane entity."
      ::= { rbnEntityTypeBackplane 17 }

rbnEntBackplaneSSR8020Data OBJECT-IDENTITY
      STATUS  current
      DESCRIPTION
              "The definitive identifier for the Smart Services Router 8020
              data backplane entity."
      ::= { rbnEntityTypeBackplane 18 }

rbnEntBackplaneSSR8010Data OBJECT-IDENTITY
      STATUS  current
      DESCRIPTION
              "The definitive identifier for the Smart Services Router 8010
              data backplane entity."
      ::= { rbnEntityTypeBackplane 19 }

rbnEntBackplaneSSR8006Data OBJECT-IDENTITY
      STATUS  current
      DESCRIPTION
              "The definitive identifier for the Smart Services Router 8006
              data backplane entity."
      ::= { rbnEntityTypeBackplane 20 }

rbnEntityTypeContainer OBJECT-IDENTITY
      STATUS  current
      DESCRIPTION
              "The top-level category identifier for entities which
              reside in the ENTITY-MIB PhysicalClass *container*"
      ::= { rbnEntities 5 }

rbnEntContainerSMS1000Data OBJECT-IDENTITY
      STATUS  current
      DESCRIPTION
              "The definitive identifier for the RedBack Networks
              SMS 1000 data container (slot) entity."
      ::= { rbnEntityTypeContainer 1 }

rbnEntContainerSMS1000Power OBJECT-IDENTITY
      STATUS  current
      DESCRIPTION
              "The definitive identifier for the RedBack Networks
              SMS 1000 power container (slot) entity."
      ::= { rbnEntityTypeContainer 2 }

rbnEntContainerSMS500Data OBJECT-IDENTITY
      STATUS  current
      DESCRIPTION
              "The definitive identifier for the RedBack Networks
              SMS 500 data container (slot) entity."
      ::= { rbnEntityTypeContainer 3 }

rbnEntContainerSMS500Power OBJECT-IDENTITY
      STATUS  current
      DESCRIPTION
              "The definitive identifier for the RedBack Networks
              SMS 500 power container (slot) entity."
      ::= { rbnEntityTypeContainer 4 }

rbnEntContainerSMS1800Data OBJECT-IDENTITY
      STATUS  current
      DESCRIPTION
              "The definitive identifier for the RedBack Networks
              SMS 1800 data container (slot) entity."
      ::= { rbnEntityTypeContainer 5 }

rbnEntContainerSMS1800Power OBJECT-IDENTITY
      STATUS  current
      DESCRIPTION
              "The definitive identifier for the RedBack Networks
              SMS 1800 power container (slot) entity."
      ::= { rbnEntityTypeContainer 6 }

rbnEntContainerSMS10000Fabric OBJECT-IDENTITY
      STATUS  current
      DESCRIPTION
              "The definitive identifier for the RedBack Networks
              SMS 10000 fabric container (slot) entity."
      ::= { rbnEntityTypeContainer 7 }

rbnEntContainerSMS10000Timing OBJECT-IDENTITY
      STATUS  current
      DESCRIPTION
              "The definitive identifier for the RedBack Networks
              SMS 10000 timing container (slot) entity."
      ::= { rbnEntityTypeContainer 8 }

rbnEntContainerSMS10000SMCM OBJECT-IDENTITY
      STATUS  current
      DESCRIPTION
              "The definitive identifier for the RedBack Networks
              SMS 10000 SM/CM container (slot) entity."
      ::= { rbnEntityTypeContainer 9 }

rbnEntContainerSMS10000IO OBJECT-IDENTITY
      STATUS  current
      DESCRIPTION
              "The definitive identifier for the RedBack Networks
              SMS 10000 IO container (slot) entity."
      ::= { rbnEntityTypeContainer 10 }




rbnEntContainerSE800Data OBJECT-IDENTITY
      STATUS current
      DESCRIPTION
              "The definitive identifier for the Redback Networks
              SE 800 data container (slot) entity."
      ::= { rbnEntityTypeContainer 14 }

rbnEntContainerSE400Data OBJECT-IDENTITY
      STATUS current
      DESCRIPTION
              "The definitive identifier for the Redback Networks
              SE 400 data container (slot) entity."
      ::= { rbnEntityTypeContainer 15 }

rbnEntContainerSE100Data OBJECT-IDENTITY
      STATUS current
      DESCRIPTION
              "The definitive identifier for the Redback Networks
              SE 100 data container (slot) entity."
      ::= { rbnEntityTypeContainer 16 }

rbnEntContainerSE100Carrier OBJECT-IDENTITY
      STATUS  current
      DESCRIPTION
              "The definitive identifier for the Redback Networks
              SE 100 carrier container (MIC-card holder) entity"
      ::= { rbnEntityTypeContainer 17 }

rbnEntContainerSE1200Data OBJECT-IDENTITY
      STATUS current
      DESCRIPTION
              "The definitive identifier for the Redback Networks
              SE 1200 data container (slot) entity."
      ::= { rbnEntityTypeContainer 18 }

rbnEntContainerSM480Data OBJECT-IDENTITY
      STATUS current
      DESCRIPTION
              "The definitive identifier for the Redback Networks
              SM480 data container (slot) entity."
      ::= { rbnEntityTypeContainer 19 }

rbnEntContainerSE600Data OBJECT-IDENTITY
      STATUS current
      DESCRIPTION
              "The definitive identifier for the Redback Networks
              SE 600 data container (slot) entity."
      ::= { rbnEntityTypeContainer 20 }

rbnEntContainerSM240Data OBJECT-IDENTITY
      STATUS current
      DESCRIPTION
              "The definitive identifier for the Redback Networks
              SM240 data container (slot) entity."
      ::= { rbnEntityTypeContainer 21 }

rbnEntContainerSE1200HData OBJECT-IDENTITY
      STATUS current
      DESCRIPTION
              "The definitive identifier for the SE1200H data
               container (slot) entity."
      ::= { rbnEntityTypeContainer 22 }

rbnEntContainerSSR8020FanTray OBJECT-IDENTITY
      STATUS current
      DESCRIPTION
              "The definitive identifier for the Smart Services Router 8020
              fan tray container (slot) entity."
      ::= { rbnEntityTypeContainer 23 }

rbnEntContainerSSR8020PowerModule OBJECT-IDENTITY
      STATUS current
      DESCRIPTION
              "The definitive identifier for the Smart Services Router 8020
              power module container (slot) entity."
      ::= { rbnEntityTypeContainer 24 }

rbnEntContainerSSR8020Data OBJECT-IDENTITY
      STATUS current
      DESCRIPTION
              "The definitive identifier for the Smart Services Router 8020
              data container (slot) entity."
      ::= { rbnEntityTypeContainer 25 }

rbnEntContainerSSR8010FanTray OBJECT-IDENTITY
      STATUS current
      DESCRIPTION
              "The definitive identifier for the Smart Services Router 8010
              fan tray container (slot) entity."
      ::= { rbnEntityTypeContainer 26 }

rbnEntContainerSSR8010PowerModule OBJECT-IDENTITY
      STATUS current
      DESCRIPTION
              "The definitive identifier for the Smart Services Router 8010
              power module container (slot) entity."
      ::= { rbnEntityTypeContainer 27 }

rbnEntContainerSSR8010Data OBJECT-IDENTITY
      STATUS current
      DESCRIPTION
              "The definitive identifier for the Smart Services Router 8010
              data container (slot) entity."
      ::= { rbnEntityTypeContainer 28 }

rbnEntContainerSSR8006FanTray OBJECT-IDENTITY
      STATUS current
      DESCRIPTION
              "The definitive identifier for the Smart Services Router 8006
              fan tray container (slot) entity."
      ::= { rbnEntityTypeContainer 29 }

rbnEntContainerSSR8006PowerModule OBJECT-IDENTITY
      STATUS current
      DESCRIPTION
              "The definitive identifier for the Smart Services Router 8006
              power module container (slot) entity."
      ::= { rbnEntityTypeContainer 30 }

rbnEntContainerSSR8006Data OBJECT-IDENTITY
      STATUS current
      DESCRIPTION
              "The definitive identifier for the Smart Services Router 8006
              data container (slot) entity."
      ::= { rbnEntityTypeContainer 31 }

rbnEntityTypePowerSupply OBJECT-IDENTITY
      STATUS  current
      DESCRIPTION
              "The top-level category identifier for entities which
              reside in the ENTITY-MIB PhysicalClass *powerSupply*"
      ::= { rbnEntities 6 }

rbnEntPowerSupplyUnknown OBJECT-IDENTITY
      STATUS  current
      DESCRIPTION
              "The identifier use to represent any power supply which
              cannot be definitively identified, probably due to the
              fact that its configuration EEPROM is not valid"
      ::= { rbnEntityTypePowerSupply 1 }

rbnEntPowerSupplySMS1000AC OBJECT-IDENTITY
      STATUS  current
      DESCRIPTION
              "The definitive identifier for the RedBack Networks
              SMS 1000 AC Power Supply, model PS-1K-AC"
      ::= { rbnEntityTypePowerSupply 2 }

rbnEntPowerSupplySMS1000DC OBJECT-IDENTITY
      STATUS  current
      DESCRIPTION
              "The definitive identifier for the RedBack Networks
              SMS 1000 DC Power Supply, model PS-1K-DC"
      ::= { rbnEntityTypePowerSupply 3 }

rbnEntPowerSupplySMS500AC OBJECT-IDENTITY
      STATUS  current
      DESCRIPTION
              "The definitive identifier for the RedBack Networks
              SMS 500 AC Power Supply"
      ::= { rbnEntityTypePowerSupply 4 }

rbnEntPowerSupplySMS500DC OBJECT-IDENTITY
      STATUS  current
      DESCRIPTION
              "The definitive identifier for the RedBack Networks
              SMS 500 DC Power Supply"
      ::= { rbnEntityTypePowerSupply 5 }

rbnEntPowerSupplySMS1800AC OBJECT-IDENTITY
      STATUS  current
      DESCRIPTION
              "The definitive identifier for the RedBack Networks
              SMS 1800 AC Power Supply"
      ::= { rbnEntityTypePowerSupply 6 }

rbnEntPowerSupplySMS1800DC OBJECT-IDENTITY
      STATUS  current
      DESCRIPTION
              "The definitive identifier for the RedBack Networks
              SMS 1800 DC Power Supply"
      ::= { rbnEntityTypePowerSupply 7 }



rbnEntPowerModuleSSR OBJECT-IDENTITY
      STATUS  current
      DESCRIPTION
              "The definitive identifier for the Smart Services Router
              Power Supply Module"
      ::= { rbnEntityTypePowerSupply 10 }

rbnEntityTypeFan OBJECT-IDENTITY
      STATUS  current
      DESCRIPTION
              "The top-level category identifier for entities which
              reside in the ENTITY-MIB PhysicalClass *fan*"
      ::= { rbnEntities 7 }

rbnEntFanSE800 OBJECT-IDENTITY
      STATUS  current
      DESCRIPTION
              "The definitive identifier for the Redback Networks
              SE 800 Fan Tray"
      ::= { rbnEntityTypeFan 1 }

rbnEntFanSE400 OBJECT-IDENTITY
      STATUS  current
      DESCRIPTION
              "The definitive identifier for the Redback Networks
              SE 400 Fan Tray"
      ::= { rbnEntityTypeFan 2 }

rbnEntFanSE1200 OBJECT-IDENTITY
      STATUS  current
      DESCRIPTION
              "The definitive identifier for the Redback Networks
              SE 1200 Fan Tray"
      ::= { rbnEntityTypeFan 3 }

rbnEntFanSM480 OBJECT-IDENTITY
      STATUS  current
      DESCRIPTION
              "The definitive identifier for the Redback Networks
              SM 480 Fan Tray"
      ::= { rbnEntityTypeFan 4 }

rbnEntFanSE600 OBJECT-IDENTITY
      STATUS  current
      DESCRIPTION
              "The definitive identifier for the Redback Networks
              SE 600 Fan Tray"
      ::= { rbnEntityTypeFan 5 }

rbnEntFanSM240 OBJECT-IDENTITY
      STATUS  current
      DESCRIPTION
              "The definitive identifier for the Redback Networks
              SM240 Fan Tray"
      ::= { rbnEntityTypeFan 6 }

rbnEntFanSE1200H OBJECT-IDENTITY
      STATUS  current
      DESCRIPTION
              "The definitive identifier for the SE1200H Fan Tray"
      ::= { rbnEntityTypeFan 7 }

rbnEntFanTraySSR OBJECT-IDENTITY
      STATUS  current
      DESCRIPTION
              "The definitive identifier for the Smart Services Router
              Fan Tray"
      ::= { rbnEntityTypeFan 8 }

rbnEntityTypeSensor OBJECT-IDENTITY
      STATUS  current
      DESCRIPTION
              "The top-level category identifier for entities which
              reside in the ENTITY-MIB PhysicalClass *sensor*"
      ::= { rbnEntities 8 }

rbnEntSensorAlarmSE400 OBJECT-IDENTITY
      STATUS  current
      DESCRIPTION
              "The definitive identifier for the Redback Networks
              SE 400 Alarm Card"
      ::= { rbnEntityTypeSensor 1 }

rbnEntSensorAlarmSE600 OBJECT-IDENTITY
      STATUS  current
      DESCRIPTION
              "The definitive identifier for the Redback Networks
              SE 600 Alarm Card"
      ::= { rbnEntityTypeSensor 2 }

rbnEntSensorAlarmSM240 OBJECT-IDENTITY
      STATUS  current
      DESCRIPTION
              "The definitive identifier for the Redback Networks
              SM 240 Alarm Card"
      ::= { rbnEntityTypeSensor 3 }

rbnEntityTypeModule OBJECT-IDENTITY
      STATUS  current
      DESCRIPTION
              "The top-level category identifier for entities which
              reside in the ENTITY-MIB PhysicalClass *module*"
      ::= { rbnEntities 9 }

rbnEntModuleUnknown OBJECT-IDENTITY
      STATUS  current
      DESCRIPTION
              "The identifier use to represent any module which
              cannot be definitively identified, probably due
              to the fact that its configuration EEPROM is not
              valid"
      ::= { rbnEntityTypeModule 1 }

rbnEntModuleSMSCE1 OBJECT-IDENTITY
      STATUS  current
      DESCRIPTION
              "The definitive identifier for the RedBack Networks
              SMS Control Engine 1"
      ::= { rbnEntityTypeModule 16 }

rbnEntModuleSMSCE2 OBJECT-IDENTITY
      STATUS  current
      DESCRIPTION
              "The definitive identifier for the RedBack Networks
              SMS Control Engine 2"
      ::= { rbnEntityTypeModule 17 }

rbnEntModuleSMSCE3 OBJECT-IDENTITY
      STATUS  current
      DESCRIPTION
              "The definitive identifier for the RedBack Networks
              SMS Control Engine 3"
      ::= { rbnEntityTypeModule 18 }

rbnEntModuleSMSFE1 OBJECT-IDENTITY
      STATUS  current
      DESCRIPTION
              "The definitive identifier for the RedBack Networks
              SMS Forwarding Engine 1"
      ::= { rbnEntityTypeModule 10 }

rbnEntModuleSMSFE2 OBJECT-IDENTITY
      STATUS  current
      DESCRIPTION
              "The definitive identifier for the RedBack Networks
              SMS Forwarding Engine 2"
      ::= { rbnEntityTypeModule 12 }

rbnEntModuleSMSFE3 OBJECT-IDENTITY
      STATUS  current
      DESCRIPTION
              "The definitive identifier for the RedBack Networks
              SMS Forwarding Engine 3"
      ::= { rbnEntityTypeModule 35 }

rbnEntModuleSMSXFE OBJECT-IDENTITY
      STATUS  current
      DESCRIPTION
              "The definitive identifier for the RedBack Networks
              SMS Extended Forwarding Engine"
      ::= { rbnEntityTypeModule 40 }

rbnEntModuleSMSFABRIC OBJECT-IDENTITY
      STATUS  current
      DESCRIPTION
              "The definitive identifier for the RedBack Networks
              SMS Switch Fabric module"
      ::= { rbnEntityTypeModule 29 }

rbnEntModuleSMSTIMING OBJECT-IDENTITY
      STATUS  current
      DESCRIPTION
              "The definitive identifier for the RedBack Networks
              SMS Timing module"
      ::= { rbnEntityTypeModule 31 }

rbnEntModuleSMSCM OBJECT-IDENTITY
      STATUS  current
      DESCRIPTION
              "The definitive identifier for the RedBack Networks
              SMS Connection Manager module"
      ::= { rbnEntityTypeModule 30 }

rbnEntModuleSMSSM OBJECT-IDENTITY
      STATUS  current
      DESCRIPTION
              "The definitive identifier for the RedBack Networks
              SMS System Manager module"
      ::= { rbnEntityTypeModule 32 }


rbnEntModuleSMSEIM OBJECT-IDENTITY
      STATUS  current
      DESCRIPTION
              "The definitive identifier for the RedBack Networks
              SMS 10/100BaseT Ethernet Interface Module"
      ::= { rbnEntityTypeModule 6 }

rbnEntModuleSMSGIGEIM OBJECT-IDENTITY
      STATUS  current
      DESCRIPTION
              "The definitive identifier for the RedBack Networks
              SMS Gigabit Ethernet Interface Module"
      ::= { rbnEntityTypeModule 26 }

rbnEntModuleSMSAIMDS3 OBJECT-IDENTITY
      STATUS  current
      DESCRIPTION
              "The definitive identifier for the RedBack Networks
              SMS ATM DS3 Interface Module"
      ::= { rbnEntityTypeModule 4 }

rbnEntModuleSMSPIME3 OBJECT-IDENTITY
      STATUS  current
      DESCRIPTION
              "The definitive identifier for the RedBack Networks
              SMS Packet E3 Interface Module"
      ::= { rbnEntityTypeModule 8 }

rbnEntModuleSMSPIME1 OBJECT-IDENTITY
      STATUS  current
      DESCRIPTION
              "The definitive identifier for the RedBack Networks
              SMS Packet E1 Interface Module"
      ::= { rbnEntityTypeModule 22 }

rbnEntModuleSMSAIME3 OBJECT-IDENTITY
      STATUS  current
      DESCRIPTION
              "The definitive identifier for the RedBack Networks
              SMS ATM E3 Interface Module"
      ::= { rbnEntityTypeModule 5 }

rbnEntModuleSMSAIME1 OBJECT-IDENTITY
      STATUS  current
      DESCRIPTION
              "The definitive identifier for the RedBack Networks
              SMS ATM E1 Interface Module"
      ::= { rbnEntityTypeModule 23 }

rbnEntModuleSMSAIMT1 OBJECT-IDENTITY
      STATUS  current
      DESCRIPTION
              "The definitive identifier for the RedBack Networks
              SMS ATM T1 Interface Module"
      ::= { rbnEntityTypeModule 20 }

rbnEntModuleSMSAIMOC3 OBJECT-IDENTITY
      STATUS  current
      DESCRIPTION
              "The definitive identifier for the RedBack Networks
              SMS ATM OC3 Interface Module"
      ::= { rbnEntityTypeModule 3 }

rbnEntModuleSMSAIMOC12 OBJECT-IDENTITY
      STATUS  current
      DESCRIPTION
              "The definitive identifier for the RedBack Networks
              SMS ATM OC12 Interface Module"
      ::= { rbnEntityTypeModule 27 }

rbnEntModuleSMSPOSOC3 OBJECT-IDENTITY
      STATUS  current
      DESCRIPTION
              "The definitive identifier for the RedBack Networks
              SMS POS OC3 Interface Module"
      ::= { rbnEntityTypeModule 24 }

rbnEntModuleSMSPOSOC12 OBJECT-IDENTITY
      STATUS  current
      DESCRIPTION
              "The definitive identifier for the RedBack Networks
              SMS POS OC12 Interface Module"
      ::= { rbnEntityTypeModule 25 }

rbnEntModuleSMSIPSEC OBJECT-IDENTITY
      STATUS  current
      DESCRIPTION
              "The definitive identifier for the RedBack Networks
              SMS IPSEC Interface Module"
      ::= { rbnEntityTypeModule 28 }

rbnEntModuleSMSPIMDS1 OBJECT-IDENTITY
      STATUS  current
      DESCRIPTION
              "The definitive identifier for the RedBack Networks
              SMS Packet DS1 Interface Module"
      ::= { rbnEntityTypeModule 14 }

rbnEntModuleSMSPIMDS3 OBJECT-IDENTITY
      STATUS  current
      DESCRIPTION
              "The definitive identifier for the RedBack Networks
              SMS Packet DS3 Interface Module"
      ::= { rbnEntityTypeModule 7 }

rbnEntModuleSMSPIMCDS3 OBJECT-IDENTITY
      STATUS  current
      DESCRIPTION
              "The definitive identifier for the RedBack Networks
              SMS Channelized DS3 Interface Module"
      ::= { rbnEntityTypeModule 15 }

rbnEntModuleSMSPIMHSSI OBJECT-IDENTITY
      STATUS  current
      DESCRIPTION
              "The definitive identifier for the RedBack Networks
              SMS Packet HSSI Interface Module"
      ::= { rbnEntityTypeModule 9 }

rbnEntModuleSEXC OBJECT-IDENTITY
      STATUS  current
      DESCRIPTION
              "The definitive identifier for the Redback Networks
              SE Cross Connect Module"
      ::= { rbnEntityTypeModule 41 }

rbnEntModuleSEEIM OBJECT-IDENTITY
      STATUS  current
      DESCRIPTION
              "The definitive identifier for the Redback Networks
              SE 10/100BaseT Ethernet Interface Module"
      ::= { rbnEntityTypeModule 42}

rbnEntModuleSEGIGEIM OBJECT-IDENTITY
      STATUS  current
      DESCRIPTION
              "The definitive identifier for the RedBack Networks
              SE Gigabit Ethernet Interface Module"
      ::= { rbnEntityTypeModule 43 }

rbnEntModuleSEPOSOC12 OBJECT-IDENTITY
      STATUS  current
      DESCRIPTION
              "The definitive identifier for the RedBack Networks
              SE POS OC12 Interface Module"
      ::= { rbnEntityTypeModule 44 }

rbnEntModuleSEPOSOC48 OBJECT-IDENTITY
      STATUS  current
      DESCRIPTION
              "The definitive identifier for the RedBack Networks
              SE POS OC48 Interface Module"
      ::= { rbnEntityTypeModule 45 }

rbnEntModuleSEPOSOC3 OBJECT-IDENTITY
      STATUS  current
      DESCRIPTION
              "The definitive identifier for the RedBack Networks
              SE POS OC3 Interface Module"
      ::= { rbnEntityTypeModule 46 }

rbnEntModuleSECHOC12DS1 OBJECT-IDENTITY
      STATUS  current
      DESCRIPTION
              "The definitive identifier for the RedBack Networks
              SE Channelized OC12 DS1 Interface Module"
      ::= { rbnEntityTypeModule 47 }

rbnEntModuleSECHOC12DS3 OBJECT-IDENTITY
      STATUS  current
      DESCRIPTION
              "The definitive identifier for the RedBack Networks
              SE Channelized OC12 DS3 Interface Module"
      ::= { rbnEntityTypeModule 48 }

rbnEntModuleSEAIMOC3 OBJECT-IDENTITY
      STATUS  current
      DESCRIPTION
              "The definitive identifier for the RedBack Networks
              SE ATM OC3 Interface Module"
      ::= { rbnEntityTypeModule 49 }

rbnEntModuleSEAIMOC12 OBJECT-IDENTITY
      STATUS  current
      DESCRIPTION
              "The definitive identifier for the RedBack Networks
              SE ATM OC12 Interface Module"
      ::= { rbnEntityTypeModule 50 }

rbnEntModuleSECHDS3 OBJECT-IDENTITY
      STATUS  current
      DESCRIPTION
              "The definitive identifier for the RedBack Networks
              SE Channelized DS3 Interface Module"
      ::= { rbnEntityTypeModule 51 }

rbnEntModuleSEDS3 OBJECT-IDENTITY
      STATUS  current
      DESCRIPTION
              "The definitive identifier for the RedBack Networks
              SE DS3 Interface Module"
      ::= { rbnEntityTypeModule 52 }

rbnEntModuleSEAIMDS3 OBJECT-IDENTITY
      STATUS  current
      DESCRIPTION
              "The definitive identifier for the RedBack Networks
              SE ATM DS3 Interface Module"
      ::= { rbnEntityTypeModule 53 }

rbnEntModuleSECHSTM1E1 OBJECT-IDENTITY
      STATUS  current
      DESCRIPTION
              "The definitive identifier for the RedBack Networks
              SE Channelized STM-1 to E1 Interface Module"
      ::= { rbnEntityTypeModule 54 }

rbnEntModuleSEE1 OBJECT-IDENTITY
      STATUS  current
      DESCRIPTION
              "The definitive identifier for the RedBack Networks
              SE E1 Interface Module"
      ::= { rbnEntityTypeModule 55 }

rbnEntModuleSEXC3 OBJECT-IDENTITY
      STATUS  current
      DESCRIPTION
              "The definitive identifier for the Redback Networks
              SE Cross Connect Module Version 3"
      ::= { rbnEntityTypeModule 56 }

rbnEntModuleSEE3 OBJECT-IDENTITY
      STATUS  current
      DESCRIPTION
              "The definitive identifier for the RedBack Networks
              SE E3 Interface Module"
      ::= { rbnEntityTypeModule 57 }

rbnEntModuleSEAIMOC12E OBJECT-IDENTITY
      STATUS  current
      DESCRIPTION
              "The definitive identifier for the RedBack Networks
              SE ATM OC12 Enhanced Interface Module"
      ::= { rbnEntityTypeModule 58 }

rbnEntModuleSEGIGETM OBJECT-IDENTITY
      STATUS  current
      DESCRIPTION
              "The definitive identifier for the RedBack Networks
              SE Gigabit Ethernet with Traffic Management Module"
      ::= { rbnEntityTypeModule 59 }

rbnEntModuleSE10GIGEIM OBJECT-IDENTITY
      STATUS  current
      DESCRIPTION
              "The definitive identifier for the RedBack Networks
              SE 10 Gigabit Ethernet Interface Module"
      ::= { rbnEntityTypeModule 60 }

rbnEntModuleSE100XC OBJECT-IDENTITY
      STATUS  current
      DESCRIPTION
              "The definitive identifier for the Redback Networks
              SE 100 Cross Connect Module"
      ::= { rbnEntityTypeModule 61 }

rbnEntModuleSE100EMIC OBJECT-IDENTITY
      STATUS  current
      DESCRIPTION
              "The definitive identifier for the RedBack Networks
              SE 100 10/100BaseT Ethernet Media Interface Connect
              Module"
      ::= { rbnEntityTypeModule 62 }

rbnEntModuleSE100FXMIC OBJECT-IDENTITY
      STATUS  current
      DESCRIPTION
              "The definitive identifier for the Redback Networks
              SE 100 FX-100 Ethernet Media Interface Connect Module"
      ::= { rbnEntityTypeModule 63 }

rbnEntModuleSE100GERJMIC OBJECT-IDENTITY
      STATUS  current
      DESCRIPTION
              "The definitive identifier for the Redback Networks
              SE 100 Gigabit Ethernet Media Interface Connect Module"
      ::= { rbnEntityTypeModule 64 }

rbnEntModuleSE100GEFXMIC OBJECT-IDENTITY
      STATUS  current
      DESCRIPTION
              "The definitive identifier for the Redback Networks
              SE 100 FX-1000 Ethernet Media Interface Connect Module"
      ::= { rbnEntityTypeModule 65 }

rbnEntModuleSEXC4 OBJECT-IDENTITY
      STATUS  current
      DESCRIPTION
              "The definitive identifier for the Redback Networks
              SE Cross Connect Module Version 4"
      ::= { rbnEntityTypeModule 66 }

rbnEntModuleSE100AIMOC3MIC OBJECT-IDENTITY
      STATUS  current
      DESCRIPTION
              "The definitive identifier for the Redback Networks
              SE 100 2-port ATM OC3 Media Interface Connect Module"
      ::= { rbnEntityTypeModule 67 }

rbnEntModuleSEASE OBJECT-IDENTITY
      STATUS  current
      DESCRIPTION
              "The definitive identifier for the Redback Networks
              SE Advanced Services Engine Module"
      ::= { rbnEntityTypeModule 68 }

rbnEntModuleSEFE60GE2 OBJECT-IDENTITY
      STATUS  current
      DESCRIPTION
              "The definitive identifier for the RedBack Networks
              FE60GE2 Ethernet Interface Module"
      ::= { rbnEntityTypeModule 69 }

rbnEntModuleSEPOSOC192 OBJECT-IDENTITY
      STATUS  current
      DESCRIPTION
              "The definitive identifier for the Redback Networks
              SE POS OC192 Media Interface Module"
      ::= { rbnEntityTypeModule 70 }

rbnEntModuleSE5PortGIGE OBJECT-IDENTITY
      STATUS  current
      DESCRIPTION
              "The definitive identifier for the Redback Networks
              5 port PPA2 based Gigabit Ethernet Media Interface Connect Module"
      ::= { rbnEntityTypeModule 71 }

rbnEntModuleSE20PortGIGE OBJECT-IDENTITY
      STATUS  current
      DESCRIPTION
              "The definitive identifier for the Redback Networks
              20 port PPA3/PMA3 based Gigabit Ethernet Media Interface Connect Module"
      ::= { rbnEntityTypeModule 72 }

rbnEntModuleSE4Port10GIGE OBJECT-IDENTITY
      STATUS  current
      DESCRIPTION
              "The definitive identifier for the Redback Networks
              4 port PPA3/PMA3 based 10 Gigabit Ethernet Media Interface Connect Module"
      ::= { rbnEntityTypeModule 73 }

rbnEntModuleSE10GIGETM OBJECT-IDENTITY
      STATUS  current
      DESCRIPTION
              "The definitive identifier for the RedBack Networks
              SE 10 Gigabit Ethernet with Traffic Management Interface Module"
      ::= { rbnEntityTypeModule 74 }

rbnEntModuleSESSE OBJECT-IDENTITY
      STATUS  current
      DESCRIPTION
              "The definitive identifier for the Redback Networks
              SmartEdge Server Engine(Winchester)"
      ::= { rbnEntityTypeModule 75 }

rbnEntModuleSE10PortGIGEDDR2 OBJECT-IDENTITY
      STATUS  current
      DESCRIPTION
               "The definitive identifier for the
               SE 10 Gigabit Ethernet with DDR Upgrade"
      ::= { rbnEntityTypeModule 76 }

rbnEntModuleSE4PortOC48 OBJECT-IDENTITY
      STATUS current
      DESCRIPTION
              "The definitive identifier for the RedBack Networks
              SE 4 port OC-48 POS  Media Interface Module"
      ::= { rbnEntityTypeModule 77 }

rbnEntModuleSE8PortOC3 OBJECT-IDENTITY
      STATUS current
      DESCRIPTION
              "The definitive identifier for the RedBack Networks
              SE 8 port OC-3 ATM Media Interface Module"
      ::= { rbnEntityTypeModule 78 }

rbnEntModuleSE8OR2PORTCHOC3OC12 OBJECT-IDENTITY
      STATUS current
      DESCRIPTION
              "The definitive identifier for the SE Channelized
              OC3/STM1 or OC12/STM4 8 or 2 Port Interface Module"
      ::= { rbnEntityTypeModule 79 }

rbnEntModuleSEASE2 OBJECT-IDENTITY
      STATUS  current
      DESCRIPTION
              "The definitive identifier for the SE Advanced Services
              Engine 2 Module"
      ::= { rbnEntityTypeModule 80 }

rbnEntModuleSE1Port10GEOC192 OBJECT-IDENTITY
      STATUS  current
      DESCRIPTION
              "The definitive identifier for the SE version of
                a line card supporting  either 10GE (gigabit ethernet) or OC192 but not both."
      ::= { rbnEntityTypeModule 81 }

rbnEntModuleSEPos8xOC3 OBJECT-IDENTITY
      STATUS current
      DESCRIPTION
              "The definitive identifier for the RedBack Networks
              SE 8 port OC-3 POS PPA2 Media Interface Module"
      ::= { rbnEntityTypeModule 82 }

rbnEntModuleSEPos4xOC12 OBJECT-IDENTITY
      STATUS current
      DESCRIPTION
              "The definitive identifier for the RedBack Networks
              SE 4 port OC-12 POS PPA2 Media Interface Module"
      ::= { rbnEntityTypeModule 83 }

rbnEntModuleSEAtm2xOC12 OBJECT-IDENTITY
      STATUS current
      DESCRIPTION
              "The definitive identifier for the RedBack Networks
              SE 2 port OC-12 ATM PPA2  Media Interface Module"
      ::= { rbnEntityTypeModule 84 }

rbnEntModuleSM10GIGEIM OBJECT-IDENTITY
      STATUS  current
      DESCRIPTION
              "The definitive identifier for the RedBack Networks
              SM 10 Gigabit Ethernet Interface Module"
      ::= { rbnEntityTypeModule 101 }

rbnEntModuleSMRP2 OBJECT-IDENTITY
      STATUS  current
      DESCRIPTION
              "The definitive identifier for the Redback Networks
              SM Routing Processor Module version 2 "
      ::= { rbnEntityTypeModule 102 }

rbnEntModuleSMGIGEIM OBJECT-IDENTITY
      STATUS  current
      DESCRIPTION
              "The definitive identifier for the RedBack Networks
              SM Gigabit Ethernet Interface Module"
      ::= { rbnEntityTypeModule 104 }

rbnEntModuleSMGIGETM OBJECT-IDENTITY
      STATUS  current
      DESCRIPTION
              "The definitive identifier for the RedBack Networks
              SM Gigabit Ethernet with Traffic Management Module"
      ::= { rbnEntityTypeModule 105 }

rbnEntModuleSM10GIGETM OBJECT-IDENTITY
      STATUS  current
      DESCRIPTION
              "The definitive identifier for the RedBack Networks
              SM 10 Gigabit Ethernet with Traffic Management
              Module"
      ::= { rbnEntityTypeModule 106 }

rbnEntModuleSMFE60GE2 OBJECT-IDENTITY
      STATUS  current
      DESCRIPTION
              "The definitive identifier for the RedBack Networks
              SM FE60GE2 Ethernet Interface Module"
      ::= { rbnEntityTypeModule 107 }

rbnEntModuleSM20PortGIGE OBJECT-IDENTITY
      STATUS  current
      DESCRIPTION
              "The definitive identifier for the Redback Networks
              SM 20 port PPA3/PMA3 based Gigabit Ethernet Media Interface Connect Module"
      ::= { rbnEntityTypeModule 108 }

rbnEntModuleSM4Port10GIGE OBJECT-IDENTITY
      STATUS  current
      DESCRIPTION
              "The definitive identifier for the Redback Networks
               SM 4 port PPA3/PMA3 based 10 Gigabit Ethernet Media Interface Connect Module"
      ::= { rbnEntityTypeModule 109 }

rbnEntModuleSM10PortGIGEDDR2 OBJECT-IDENTITY
      STATUS  current
      DESCRIPTION
               "The definitive identifier for the SM version of
               the 10 Gigabit Ethernet with DDR Upgrade"
      ::= { rbnEntityTypeModule 110 }

rbnEntModuleSM1Port10GEOC192 OBJECT-IDENTITY
      STATUS  current
      DESCRIPTION
               "The definitive identifier for the SM version of
                a line card supporting  either 10GE (gigabit ethernet) or OC192 but not both."
      ::= { rbnEntityTypeModule 111 }

rbnEntModuleSM8OR2PORTCHOC3OC12 OBJECT-IDENTITY
      STATUS current
      DESCRIPTION
              "The definitive identifier for the SM Channelized
              OC3/STM1 or OC12/STM4 8 or 2 Port Interface Module"
      ::= { rbnEntityTypeModule 112 }

rbnEntModuleSSRALSW OBJECT-IDENTITY
      STATUS  current
      DESCRIPTION
              "The definitive identifier for the Smart Services Router
              Alarm with Switch Fabric module."
      ::= { rbnEntityTypeModule 201 }

rbnEntModuleSSRRPSW OBJECT-IDENTITY
      STATUS  current
      DESCRIPTION
              "The definitive identifier for the Smart Services Router
              Route Processor with Switch Fabric module."
      ::= { rbnEntityTypeModule 202 }

rbnEntModuleSSRSW OBJECT-IDENTITY
      STATUS  current
      DESCRIPTION
              "The definitive identifier for the Smart Services Router
              Switch module."
      ::= { rbnEntityTypeModule 203 }

rbnEntModuleSSR40Port1GE OBJECT-IDENTITY
      STATUS  current
      DESCRIPTION
              "The definitive identifier for the Smart Services Router
              40 port 1 Gigabit Ethernet Interface Module."
      ::= { rbnEntityTypeModule 204 }

rbnEntModuleSSR10Port10GE OBJECT-IDENTITY
      STATUS  current
      DESCRIPTION
              "The definitive identifier for the Smart Services Router
              10 port 10 Gigabit Ethernet Interface Module."
      ::= { rbnEntityTypeModule 205 }

rbnEntModuleSSC1 OBJECT-IDENTITY
      STATUS current
      DESCRIPTION
              "The definitive identifier for the Smart Services Card
              with Storage (SSC1)"
      ::= { rbnEntityTypeModule 207 }

rbnEntModuleSSR2Port40GEor100GE OBJECT-IDENTITY
      STATUS  current
      DESCRIPTION
              "The definitive identifier for the Smart Services Router
              1 port 100 Gigabit or 2 port 40 Gigabit Ethernet Interface Module."
      ::= { rbnEntityTypeModule 210 }

rbnEntityTypePort OBJECT-IDENTITY
      STATUS  current
      DESCRIPTION
              "The top-level category identifier for entities which
              reside in the ENTITY-MIB PhysicalClass *port*"
      ::= { rbnEntities 10 }

rbnEntPortUnknown OBJECT-IDENTITY
      STATUS  current
      DESCRIPTION
              "The identifier use to represent any module which
              cannot be definitively identified, probably due
              to the fact that its configuration EEPROM is not
              valid"
      ::= { rbnEntityTypePort 1 }

rbnEntPortSMSCE1MGMT OBJECT-IDENTITY
      STATUS  current
      DESCRIPTION
              "The definitive identifier for the RedBack Networks
              SMS Control Engine 1, Local Management Port"
      ::= { rbnEntityTypePort 16 }

rbnEntPortSMSCE2MGMT OBJECT-IDENTITY
      STATUS  current
      DESCRIPTION
              "The definitive identifier for the RedBack Networks
              SMS Control Engine 2, Local Management Port"
      ::= { rbnEntityTypePort 17 }

rbnEntPortSMSCE3MGMT OBJECT-IDENTITY
      STATUS  current
      DESCRIPTION
              "The definitive identifier for the RedBack Networks
              SMS Control Engine 3, Local Management Port"
      ::= { rbnEntityTypePort 18 }


rbnEntPortSMSEIM OBJECT-IDENTITY
      STATUS  current
      DESCRIPTION
              "The definitive identifier for the RedBack Networks
              SMS 10/100BaseT Ethernet Interface Port"
      ::= { rbnEntityTypePort 6 }

rbnEntPortSMSGIGEIM OBJECT-IDENTITY
      STATUS  current
      DESCRIPTION
              "The definitive identifier for the RedBack Networks
              SMS Gigabit Ethernet Interface Port"
      ::= { rbnEntityTypePort 26 }

rbnEntPortSMSAIMDS3 OBJECT-IDENTITY
      STATUS  current
      DESCRIPTION
              "The definitive identifier for the RedBack Networks
              SMS ATM DS3 Interface Port"
      ::= { rbnEntityTypePort 4 }

rbnEntPortSMSPIME3 OBJECT-IDENTITY
      STATUS  current
      DESCRIPTION
              "The definitive identifier for the RedBack Networks
              SMS Packet E3 Interface Port"
      ::= { rbnEntityTypePort 8 }

rbnEntPortSMSPIME1 OBJECT-IDENTITY
      STATUS  current
      DESCRIPTION
              "The definitive identifier for the RedBack Networks
              SMS Packet E1 Interface Port"
      ::= { rbnEntityTypePort 22 }

rbnEntPortSMSAIME3 OBJECT-IDENTITY
      STATUS  current
      DESCRIPTION
              "The definitive identifier for the RedBack Networks
              SMS ATM E3 Interface Port"
      ::= { rbnEntityTypePort 5 }

rbnEntPortSMSAIME1 OBJECT-IDENTITY
      STATUS  current
      DESCRIPTION
              "The definitive identifier for the RedBack Networks
              SMS ATM E1 Interface Port"
      ::= { rbnEntityTypePort 23 }

rbnEntPortSMSAIMT1 OBJECT-IDENTITY
      STATUS  current
      DESCRIPTION
              "The definitive identifier for the RedBack Networks
              SMS ATM T1 Interface Port"
      ::= { rbnEntityTypePort 20 }

rbnEntPortSMSAIMOC3 OBJECT-IDENTITY
      STATUS  current
      DESCRIPTION
              "The definitive identifier for the RedBack Networks
              SMS ATM OC3 Interface Port"
      ::= { rbnEntityTypePort 3 }

rbnEntPortSMSAIMOC12 OBJECT-IDENTITY
      STATUS  current
      DESCRIPTION
              "The definitive identifier for the RedBack Networks
              SMS ATM OC12 Interface Port"
      ::= { rbnEntityTypePort 27 }

rbnEntPortSMSPOSOC3 OBJECT-IDENTITY
      STATUS  current
      DESCRIPTION
              "The definitive identifier for the RedBack Networks
              SMS POS OC3 Interface Port"
      ::= { rbnEntityTypePort 24 }

rbnEntPortSMSPOSOC12 OBJECT-IDENTITY
      STATUS  current
      DESCRIPTION
              "The definitive identifier for the RedBack Networks
              SMS POS OC12 Interface Port"
      ::= { rbnEntityTypePort 25 }

rbnEntPortSMSPIMDS1 OBJECT-IDENTITY
      STATUS  current
      DESCRIPTION
              "The definitive identifier for the RedBack Networks
              SMS Packet DS1 Interface Port"
      ::= { rbnEntityTypePort 14 }

rbnEntPortSMSPIMDS3 OBJECT-IDENTITY
      STATUS  current
      DESCRIPTION
              "The definitive identifier for the RedBack Networks
              SMS Packet DS3 Interface Port"
      ::= { rbnEntityTypePort 7 }

rbnEntPortSMSPIMCDS3 OBJECT-IDENTITY
      STATUS  current
      DESCRIPTION
              "The definitive identifier for the RedBack Networks
              SMS Channelized DS3 Interface Port"
      ::= { rbnEntityTypePort 15 }

rbnEntPortSMSPIMHSSI OBJECT-IDENTITY
      STATUS  current
      DESCRIPTION
              "The definitive identifier for the RedBack Networks
              SMS Packet HSSI Interface Port"
      ::= { rbnEntityTypePort 9 }

rbnEntPortSEXCMGMT OBJECT-IDENTITY
      STATUS  current
      DESCRIPTION
              "The definitive identifier for the Redback Networks
              SE Cross Connect, Local Management Port"
      ::= { rbnEntityTypePort 41 }

rbnEntPortSEEIM OBJECT-IDENTITY
      STATUS  current
      DESCRIPTION
              "The definitive identifier for the RedBack Networks
              SE 10/100BaseT Ethernet Interface Port"
      ::= { rbnEntityTypePort 42 }

rbnEntPortSEGIGEIM OBJECT-IDENTITY
      STATUS  current
      DESCRIPTION
              "The definitive identifier for the RedBack Networks
              SE Gigabit Ethernet Interface Port"
      ::= { rbnEntityTypePort 43 }

rbnEntPortSEPOSOC12 OBJECT-IDENTITY
      STATUS  current
      DESCRIPTION
              "The definitive identifier for the RedBack Networks
              SE POS OC12 Interface Port"
      ::= { rbnEntityTypePort 44 }

rbnEntPortSEPOSOC48 OBJECT-IDENTITY
      STATUS  current
      DESCRIPTION
              "The definitive identifier for the RedBack Networks
              SE POS OC48 Interface Port"
      ::= { rbnEntityTypePort 45 }

rbnEntPortSEPOSOC3 OBJECT-IDENTITY
      STATUS  current
      DESCRIPTION
              "The definitive identifier for the RedBack Networks
              SE POS OC3 Interface Port"
      ::= { rbnEntityTypePort 46 }

rbnEntPortSECHOC12DS1 OBJECT-IDENTITY
      STATUS  current
      DESCRIPTION
              "The definitive identifier for the RedBack Networks
              SE Channelized OC12 DS1 Interface Port"
      ::= { rbnEntityTypePort 47 }

rbnEntPortSECHOC12DS3 OBJECT-IDENTITY
      STATUS  current
      DESCRIPTION
              "The definitive identifier for the RedBack Networks
              SE Channelized OC12 DS3 Interface Port"
      ::= { rbnEntityTypePort 48 }

rbnEntPortSEAIMOC3 OBJECT-IDENTITY
      STATUS  current
      DESCRIPTION
              "The definitive identifier for the RedBack Networks
              SE ATM OC3 Interface Port"
      ::= { rbnEntityTypePort 49 }

rbnEntPortSEAIMOC12 OBJECT-IDENTITY
      STATUS  current
      DESCRIPTION
              "The definitive identifier for the RedBack Networks
              SE ATM OC12 Interface Port"
      ::= { rbnEntityTypePort 50 }

rbnEntPortSECHDS3 OBJECT-IDENTITY
      STATUS  current
      DESCRIPTION
              "The definitive identifier for the RedBack Networks
              SE Channelized DS3 Interface Port"
      ::= { rbnEntityTypePort 51 }

rbnEntPortSEDS3 OBJECT-IDENTITY
      STATUS  current
      DESCRIPTION
              "The definitive identifier for the RedBack Networks
              SE DS3 Interface Port"
      ::= { rbnEntityTypePort 52 }

rbnEntPortSEAIMDS3 OBJECT-IDENTITY
      STATUS  current
      DESCRIPTION
              "The definitive identifier for the RedBack Networks
              SE ATM DS3 Interface Port"
      ::= { rbnEntityTypePort 53 }

rbnEntPortSECHSTM1E1 OBJECT-IDENTITY
      STATUS  current
      DESCRIPTION
              "The definitive identifier for the RedBack Networks
              SE Channelized STM-1 to E1 Interface Port"
      ::= { rbnEntityTypePort 54 }

rbnEntPortSEE1 OBJECT-IDENTITY
      STATUS  current
      DESCRIPTION
              "The definitive identifier for the RedBack Networks
              SE E1 Interface Port"
      ::= { rbnEntityTypePort 55 }

rbnEntPortSEXC3MGMT OBJECT-IDENTITY
      STATUS  current
      DESCRIPTION
              "The definitive identifier for the Redback Networks
              SE Cross Connect 3, Local Management Port"
      ::= { rbnEntityTypePort 56 }

rbnEntPortSEE3 OBJECT-IDENTITY
      STATUS  current
      DESCRIPTION
              "The definitive identifier for the RedBack Networks
              SE E3 Interface Port"
      ::= { rbnEntityTypePort 57 }

rbnEntPortSEAIMOC12E OBJECT-IDENTITY
      STATUS  current
      DESCRIPTION
              "The definitive identifier for the RedBack Networks
              SE ATM OC12 Enhanced Interface Port"
      ::= { rbnEntityTypePort 58 }

rbnEntPortSEGIGETM OBJECT-IDENTITY
      STATUS  current
      DESCRIPTION
              "The definitive identifier for the RedBack Networks
              SE Gigabit Ethernet with Traffic Management Interface
              Port"
      ::= { rbnEntityTypePort 59 }

rbnEntPortSE10GIGEIM OBJECT-IDENTITY
      STATUS  current
      DESCRIPTION
              "The definitive identifier for the RedBack Networks
              SE 10 Gigabit Ethernet Interface Port"
      ::= { rbnEntityTypePort 60 }

rbnEntPortSE100XCMGMT OBJECT-IDENTITY
      STATUS  current
      DESCRIPTION
              "The definitive identifier for the Redback Networks
              SE 100 Cross Connect, Local Management Port"
      ::= { rbnEntityTypePort 61 }

rbnEntPortSE100EIM OBJECT-IDENTITY
      STATUS  current
      DESCRIPTION
              "The definitive identifier for the RedBack Networks
              SE 100 10/100BaseT Ethernet Interface Port"
      ::= { rbnEntityTypePort 62 }

rbnEntPortSE100FXIM OBJECT-IDENTITY
      STATUS  current
      DESCRIPTION
              "The definitive identifier for the RedBack Networks
              SE 100 FX-100 Ethernet Interface Port"
      ::= { rbnEntityTypePort 63 }

rbnEntPortSE100GERJIM OBJECT-IDENTITY
      STATUS  current
      DESCRIPTION
              "The definitive identifier for the RedBack Networks
              SE 100 Gigabit Ethernet Interface Port"
      ::= { rbnEntityTypePort 64 }

rbnEntPortSE100GEFXIM OBJECT-IDENTITY
      STATUS  current
      DESCRIPTION
              "The definitive identifier for the RedBack Networks
              SE 100 FX-1000 Ethernet Interface Port"
      ::= { rbnEntityTypePort 65 }

rbnEntPortSEXC4MGMT OBJECT-IDENTITY
      STATUS  current
      DESCRIPTION
              "The definitive identifier for the Redback Networks
              SE Cross Connect 4, Local Management Port"
      ::= { rbnEntityTypePort 66 }


rbnEntPortSE100AIMOC3 OBJECT-IDENTITY
      STATUS  current
      DESCRIPTION
              "The definitive identifier for the RedBack Networks
              SE 100 ATM OC3 Interface Port"
      ::= { rbnEntityTypePort 67 }

rbnEntPortSEPOSOC192 OBJECT-IDENTITY
      STATUS  current
      DESCRIPTION
              "The definitive identifier for the RedBack Networks
              SE POS OC192 Interface Port"
      ::= { rbnEntityTypePort 68 }

rbnEntPortSE10GIGETM OBJECT-IDENTITY
      STATUS  current
      DESCRIPTION
              "The definitive identifier for the RedBack Networks
              SE 10 Gigabit Ethernet with Traffic Management Interface Port"
      ::= { rbnEntityTypePort 69 }

rbnEntPortSECHOC3OC12 OBJECT-IDENTITY
      STATUS  current
      DESCRIPTION
              "The definitive identifier for the SE Channelized
              OC3/STM1 or OC12/STM4 Interface Port"
      ::= { rbnEntityTypePort 70 }

rbnEntPortSECHOC3 OBJECT-IDENTITY
      STATUS  current
      DESCRIPTION
              "The definitive identifier for the SE Channelized
              OC3/STM1 Interface Port"
      ::= { rbnEntityTypePort 71 }

rbnEntPortSM10GIGEIM OBJECT-IDENTITY
      STATUS  current
      DESCRIPTION
              "The definitive identifier for the RedBack Networks
              SM 10 Gigabit Ethernet Interface Port"
      ::= { rbnEntityTypePort 101 }

rbnEntPortSMRPMGMT OBJECT-IDENTITY
      STATUS  current
      DESCRIPTION
              "The definitive identifier for the Redback Networks
                SM Routing Processor, Local Management Port"
      ::= { rbnEntityTypePort 103 }

rbnEntPortSMGIGEIM OBJECT-IDENTITY
      STATUS  current
      DESCRIPTION
              "The definitive identifier for the RedBack Networks
              SM Gigabit Ethernet Interface Port"
      ::= { rbnEntityTypePort 104 }

rbnEntPortSMGIGETM OBJECT-IDENTITY
      STATUS  current
      DESCRIPTION
              "The definitive identifier for the RedBack Networks
              SM Gigabit Ethernet with Traffic Management Interface
              Port"
      ::= { rbnEntityTypePort 105 }

rbnEntPortSM10GIGETM OBJECT-IDENTITY
      STATUS  current
      DESCRIPTION
              "The definitive identifier for the RedBack Networks
              SM 10 Gigabit Ethernet with Traffic Management port"
      ::= { rbnEntityTypePort 106 }


rbnEntPortSMEIM OBJECT-IDENTITY
      STATUS  current
      DESCRIPTION
              "The definitive identifier for the RedBack Networks
              SM 10/100BaseT Ethernet Interface Port"
      ::= { rbnEntityTypePort 107 }

rbnEntPortSMCHOC3OC12 OBJECT-IDENTITY
      STATUS  current
      DESCRIPTION
              "The definitive identifier for the SM Channelized
              OC3/STM1 or OC12/STM4 Interface Port"
      ::= { rbnEntityTypePort 108 }

rbnEntPortSMCHOC3 OBJECT-IDENTITY
      STATUS  current
      DESCRIPTION
              "The definitive identifier for the SM Channelized
              OC3/STM1 Interface Port"
      ::= { rbnEntityTypePort 109 }

rbnEntPortSSR1GE OBJECT-IDENTITY
      STATUS  current
      DESCRIPTION
              "The definitive identifier for the Smart Services Router
              1 Gigabit Ethernet Interface Port"
      ::= { rbnEntityTypePort 201 }

rbnEntPortSSR10GE OBJECT-IDENTITY
      STATUS  current
      DESCRIPTION
              "The definitive identifier for the Smart Services Router
              10 Gigabit Ethernet Interface Port"
      ::= { rbnEntityTypePort 202 }

rbnEntPortSSRRPSWMgmt OBJECT-IDENTITY
      STATUS  current
      DESCRIPTION
              "The definitive identifier for the Smart Services Router
              Route Processor with Switch Fabric card Local Management Port"
      ::= { rbnEntityTypePort 203 }

rbnEntPortSSR100GE OBJECT-IDENTITY
      STATUS  current
      DESCRIPTION
              "The definitive identifier for the Smart Services Router
               100 Gigabit Ethernet Interface Port"
      ::= { rbnEntityTypePort 204 }

rbnEntPortSSR40GE OBJECT-IDENTITY
      STATUS  current
      DESCRIPTION
              "The definitive identifier for the Smart Services Router
               40 Gigabit Ethernet Interface Port"
      ::= { rbnEntityTypePort 205 }

rbnEntPortSSR40GEor100GE OBJECT-IDENTITY
      STATUS  current
      DESCRIPTION
              "The definitive identifier for the Smart Services Router
               40 or 100 Gigabit Ethernet Interface Port"
      ::= { rbnEntityTypePort 206 }

rbnEntityTypeStack OBJECT-IDENTITY
      STATUS  current
      DESCRIPTION
              "The top-level category identifier for entities which
              reside in the ENTITY-MIB PhysicalClass *module*"
      ::= { rbnEntities 11 }

rbnEntityTypeCPU OBJECT-IDENTITY
      STATUS  current
      DESCRIPTION
              "The top-level category identifier for entities which
              reside in the ENTITY-MIB PhysicalClass *module*"
      ::= { rbnEntities 12 }

rbnEntCpuUnknown OBJECT-IDENTITY
      STATUS  current
      DESCRIPTION
              "The identifier use to represent any cpu which
              cannot be definitively identified."
      ::= { rbnEntityTypeCPU 1 }

rbnEntCpuOcteon OBJECT-IDENTITY
STATUS  current
      DESCRIPTION
              "The definitive identifier for the RedBack Networks
              Octeon Processor."
      ::= { rbnEntityTypeCPU 2 }

rbnEntityTypeDisk OBJECT-IDENTITY
      STATUS  current
      DESCRIPTION
              "The top-level category identifier for entities which
              reside in the ENTITY-MIB PhysicalClass *module*"
      ::= { rbnEntities 13 }

rbnEntDiskUnknown OBJECT-IDENTITY
      STATUS  current
      DESCRIPTION
              "The identifier use to represent any disk which
              cannot be definitively identified."
      ::= { rbnEntityTypeDisk 1 }

rbnEntDiskSSE OBJECT-IDENTITY
      STATUS  current
      DESCRIPTION
              "The definitive identifier for the RedBack Networks
              removable disks on SSE card."
      ::= { rbnEntityTypeDisk 2 }

rbnEntityTypeMemory OBJECT-IDENTITY
      STATUS  current
      DESCRIPTION
              "The top-level category identifier for entities which
              reside in the ENTITY-MIB PhysicalClass *module*"
      ::= { rbnEntities 14 }

END
