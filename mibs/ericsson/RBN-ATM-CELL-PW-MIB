-- *****************************************************************
-- RBN-ATM-CELL-PW-MIB   Redback MIB for ATM Cell Pseudo Wires that
--                       carry AAL2/AAL5 cell traffic.
--
-- Copyright (c) 2007 RedBack Networks, Inc.
-- All rights reserved.
--
-- *****************************************************************

RBN-ATM-CELL-PW-MIB DEFINITIONS ::= BEGIN

IMPORTS
    MODULE-IDENTITY,
    OBJECT-TYPE,
    Counter32
        FROM SNMPv2-SMI

    MODULE-COMPLIANCE,
    OBJECT-GROUP
        FROM SNMPv2-CONF

    RbnCircuitHandle
        FROM RBN-TC

    rbnMgmt
        FROM RBN-SMI;

rbnAtmCellPWMIB MODULE-IDENTITY
    LAST-UPDATED "200705300000Z" -- May 30, 2007
    ORGANIZATION "Redback Networks, Inc."
        CONTACT-INFO
        "               Redback Networks, Inc.
                Postal: 300 Holger Way
                        San Jose, CA  95134
                        USA

                 Phone: +1 408 750 5000
                   Fax: +1 408 750 5599

                E-mail: mib-info@redback.com
                "
    DESCRIPTION
       "The MIB for managing the ATM Cell Pseudo Wire circuits that
        are used to carry ATM traffic. "

    REVISION      "200705300000Z" -- May 30, 2007
    DESCRIPTION
                "Initial version."

    ::= { rbnMgmt 41 }


rbnAtmCellPWObjects OBJECT IDENTIFIER ::= { rbnAtmCellPWMIB 1 }

rbnAtmCellPWStatTable   OBJECT-TYPE
    SYNTAX       SEQUENCE OF RbnAtmCellPWStatEntry
    MAX-ACCESS   not-accessible
    STATUS       current
    DESCRIPTION
        "This table provides a collection of objects providing
        statistics of a  ATM Cell Pseudo wire circuit that is
        used to carry ATM traffic."
    ::= { rbnAtmCellPWObjects 1 }

rbnAtmCellPWStatEntry    OBJECT-TYPE
    SYNTAX       RbnAtmCellPWStatEntry
    MAX-ACCESS   not-accessible
    STATUS       current
    DESCRIPTION
        "Each entry in this table represents a statistics per ATM Cell
         Pseudo Wire circuit. This table is indexed by Pseudo Wire
         circuit handle. "
    INDEX { rbnAtmCellPWCircuitHandle }
    ::= { rbnAtmCellPWStatTable 1 }

    RbnAtmCellPWStatEntry ::= SEQUENCE {
        rbnAtmCellPWCircuitHandle       RbnCircuitHandle,
        rbnAtmCellPWOutOfSeqDrops       Counter32,
        rbnAtmCellPWCellConcatDrops     Counter32
    }


rbnAtmCellPWCircuitHandle      OBJECT-TYPE
    SYNTAX       RbnCircuitHandle
    MAX-ACCESS   not-accessible
    STATUS       current
    DESCRIPTION
        "A key for identifing the PW circuit. See the definition
        of the RbnCircuitHandle TEXTUAL-CONVENTION for the definition
        of this circuit handle."
    ::= { rbnAtmCellPWStatEntry 1 }

rbnAtmCellPWOutOfSeqDrops   OBJECT-TYPE
    SYNTAX       Counter32
    MAX-ACCESS   read-only
    STATUS       current
    DESCRIPTION
        "The total number of cells that dropped because of
        out-of-sequence PDUs received on the PW circuit."
    ::= { rbnAtmCellPWStatEntry 2 }

rbnAtmCellPWCellConcatDrops   OBJECT-TYPE
    SYNTAX       Counter32
    MAX-ACCESS   read-only
    STATUS       current
    DESCRIPTION
        "The total number of cells that dropped because of
        cell-concatenated PDUs received on the PW circuit."
    ::= { rbnAtmCellPWStatEntry 3 }


-- Conformance Information

rbnAtmCellPWMIBConformance OBJECT IDENTIFIER ::=
    { rbnAtmCellPWMIB 2 }

rbnAtmCellPWMIBGroups OBJECT IDENTIFIER ::=
    { rbnAtmCellPWMIBConformance 1 }

rbnAtmCellPWMIBCompliances OBJECT IDENTIFIER ::=
    { rbnAtmCellPWMIBConformance 2 }


-- Compliance Statements

rbnAtmCellPWMIBCompliance MODULE-COMPLIANCE
    STATUS      current
    DESCRIPTION
        "The compliance statement for RedBack Networks
        SNMP entities which represent ATM Cell PW circuit."
    MODULE      -- this module
    MANDATORY-GROUPS {
        rbnAtmCellPWStatGroup
        }
    ::= { rbnAtmCellPWMIBCompliances 1 }

--
-- groupings
--

rbnAtmCellPWStatGroup OBJECT-GROUP
    OBJECTS {
        rbnAtmCellPWOutOfSeqDrops,
        rbnAtmCellPWCellConcatDrops
    }
    STATUS      current
    DESCRIPTION
        "The collection of objects which represent PW circuit statistics."
    ::= { rbnAtmCellPWMIBGroups 1 }

END
