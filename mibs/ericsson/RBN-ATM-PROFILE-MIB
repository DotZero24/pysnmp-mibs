-- *****************************************************************
-- RBN-ATM-PROFILE-MIB
--
-- Copyright (c) 1998, 2001-2002 RedBack Networks, Inc.
-- All rights reserved.
--
-- *****************************************************************

RBN-ATM-PROFILE-MIB DEFINITIONS ::= BEGIN

IMPORTS
	MODULE-IDENTITY,
	OBJECT-TYPE,
	Integer32
		FROM SNMPv2-SMI
	TEXTUAL-CONVENTION,
	TruthValue
		FROM SNMPv2-TC
	MODULE-COMPLIANCE,
	OBJECT-GROUP
		FROM SNMPv2-CONF
	atmTrafficDescrParamEntry
		FROM ATM-MIB
	rbnMgmt
		FROM RBN-SMI;

rbnAtmProfileMIB MODULE-IDENTITY
	LAST-UPDATED	"200204190000Z" -- Apr 19, 2002
	ORGANIZATION	"RedBack Networks, Inc."
        CONTACT-INFO
		"	RedBack Networks, Inc.

		Postal:	300 Holger Way
			San Jose, CA  95134-1362
			USA

		 Phone:	+1 408 570 5000
		   Fax: +1 408 570 5599

		E-mail:	mib-info@RedBackNetworks.com"
	DESCRIPTION
		"The MIB for instrumenting parameters associated with
		an ATM profile (traffic descriptor) beyond those
		instrumented by standards-track	MIBs."

	REVISION	"200204190000Z" -- Apr 19, 2002
	DESCRIPTION
                "Changed DEFVAL of rbnAtmTransmitBuffers from 1
                to 50"

	REVISION	"200112110000Z" -- December 11, 2001
	DESCRIPTION
		"Changed the CONTACT-INFO to reflect Redback's
		current postal address and phone numbers.
		Changed the default value for rbnAtmTransmitBuffers.
		Imported Integer32 from SNMPv2-SMI."
	REVISION	"9807151645Z" -- July 15, 1998
	DESCRIPTION
		"Initial version"
	::= { rbnMgmt 2 }


AtmProfileName ::= TEXTUAL-CONVENTION
	DISPLAY-HINT	"80a"
	STATUS		current
	DESCRIPTION
		"This data type is used to model an administratively
		assigned name as an identifier of an ATM profile."
	SYNTAX		OCTET STRING (SIZE (0..80))

rbnAtmProfileMIBObjects OBJECT IDENTIFIER ::= { rbnAtmProfileMIB 1 }

rbnAtmProfileTable   OBJECT-TYPE
	SYNTAX       SEQUENCE OF RbnAtmProfileEntry
	MAX-ACCESS   not-accessible
	STATUS       current
	DESCRIPTION
		"This table provides a collection of auxiliary
		objects	providing parameters for atm profiles."
	::= { rbnAtmProfileMIBObjects 1 }

rbnAtmProfileEntry   OBJECT-TYPE
	SYNTAX       RbnAtmProfileEntry
	MAX-ACCESS   not-accessible
	STATUS       current
	DESCRIPTION
		"Each entry in this table represents a profile."
	AUGMENTS { atmTrafficDescrParamEntry }
	::= { rbnAtmProfileTable 1 }


RbnAtmProfileEntry ::=
	SEQUENCE {
		rbnAtmProfileName	AtmProfileName,
		rbnAtmCountersEnabled	TruthValue,
		rbnAtmCellLossPriority	TruthValue,
		rbnAtmTransmitBuffers	Integer32
	}


rbnAtmProfileName    OBJECT-TYPE
	SYNTAX       AtmProfileName
	MAX-ACCESS   read-create
	STATUS       current
	DESCRIPTION
		"The textual handle assigned to an instance of
		the rbnAtmProfileTable (and via augmentation, the
		atmTrafficDescrParamTable).  Using a textual handle
		instead of an arbitrary integer (such as
		atmTrafficDescrParamIndex) allows a configuration
		to contain human-friendly cross-references to the
		profiles from those places where they are used,
		such as in circuit configuration tables."
	DEFVAL { ''H }
	::= { rbnAtmProfileEntry 1 }

rbnAtmCountersEnabled    OBJECT-TYPE
	SYNTAX       TruthValue
	MAX-ACCESS   read-create
	STATUS       current
	DESCRIPTION
		"An indication as to whether circuits configured
		with this profile should enable per-circuit
		statistical counters.  An ATM circuit will only
		keep per-circuit statistical counters if this
		object is set to true(1) in the profile being used
		by the circuit."
	DEFVAL { false }
	::= { rbnAtmProfileEntry 2 }

rbnAtmCellLossPriority    OBJECT-TYPE
	SYNTAX       TruthValue
	MAX-ACCESS   read-create
	STATUS       current
	DESCRIPTION
		"An indication as to whether circuits configured
		with this profile should enable the Cell Loss
		Priority (CLP) bit on transmitted cells. If the profile
		being used by a circuit has this object set to true(1),
		then all cells transmitted on that circuit will have the
		CLP bit set."
	::= { rbnAtmProfileEntry 3 }

rbnAtmTransmitBuffers    OBJECT-TYPE
	SYNTAX       Integer32 (1..63)
	MAX-ACCESS   read-create
	STATUS       current
	DESCRIPTION
		"This object limits the total number of outbound
		transmit packet buffers that may be consumed by
		the circuit that references the profile.

		Note well that this parameter should be used with
		caution.  Improper setting can have severe
		consequences on overall system performance."
	DEFVAL { 50 }
	::= { rbnAtmProfileEntry 4 }


-- Conformance Information

rbnAtmProfileMIBConformance OBJECT IDENTIFIER ::=
	{ rbnAtmProfileMIB 2 }

rbnAtmProfileMIBGroups OBJECT IDENTIFIER ::=
	{ rbnAtmProfileMIBConformance 1 }

rbnAtmProfileMIBCompliances OBJECT IDENTIFIER ::=
	{ rbnAtmProfileMIBConformance 2 }


-- Compliance Statements

rbnAtmProfileMIBCompliance MODULE-COMPLIANCE
	STATUS	    current
	DESCRIPTION
		"The compliance statement for RedBack Networks
		SNMP entities which represent AAL5 VCL statistics"
	MODULE	    -- this module
	MANDATORY-GROUPS {
		rbnAtmProfileGroup
		}
	::= { rbnAtmProfileMIBCompliances 1 }

-- Units of Conformance

rbnAtmProfileGroup OBJECT-GROUP
	OBJECTS {
		rbnAtmProfileName,
		rbnAtmCountersEnabled,
		rbnAtmCellLossPriority,
		rbnAtmTransmitBuffers
	}
	STATUS	    current
	DESCRIPTION
		"A collection of objects providing supplemental
		AAL5 VCL information beyond that supplied by
		IETF standards-track MIBs"
	::= { rbnAtmProfileMIBGroups 1 }

END
