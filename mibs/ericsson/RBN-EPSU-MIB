-- **********************************************************************
-- RBN-EPSU-MIB     Evolved Packet System (EPS) User plane statistics MIB
--
-- Copyright (c) 2009 Redback Networks, Inc.
-- All rights reserved.
--
-- **********************************************************************

RBN-EPSU-MIB DEFINITIONS ::= BEGIN

IMPORTS
    OBJECT-TYPE, MODULE-IDENTITY,
    Unsigned32, Counter64
        FROM SNMPv2-SMI

    MODULE-COMPLIANCE, OBJECT-GROUP
        FROM SNMPv2-CONF

    SnmpAdminString
        FROM SNMP-FRAMEWORK-MIB

    rbnMgmt
        FROM RBN-SMI;

rbnEpsuMIB MODULE-IDENTITY
    LAST-UPDATED "200909231200Z" -- Sept 23, 2009
    ORGANIZATION    "Redback Networks, Inc."
    CONTACT-INFO
        "        Redback Networks, Inc.

         Postal: 300 Holger Way
                 San Jose, CA  95134
                 USA

         Phone: +1 408 750 5000
         Fax: +1 408 750 5599
        "
    DESCRIPTION
       "Evolved Packet System (EPS) user plane statistics."

    REVISION "200909231200Z" -- Sept 23, 2009
    DESCRIPTION
       "Initial version."
    ::= { rbnMgmt 47 }


--
-- Objects
--
rbnEpsuStatMIBObjects   OBJECT IDENTIFIER ::= { rbnEpsuMIB 1 }

--
-- The rbnEpsuS1uGtp counter group will count all GTP tunnel packets
-- containing user payload data that is sent and received between eNodeBs
-- and the Serving or Combined Gateway (SGW or CGW) on the GTP based S1-U
-- interface.  The byte counters include the length which is defined as
-- (tunnel IP header + GTP header + user data IP packet).  Discarded packets
-- are those received in the uplink direction that have errors in the tunnel
-- IP header, or GTP header, or there are insufficient resources (e.g.
-- buffer memory) and the packet cannot be processed further.  Dropped
-- packets are those which were supposed  to be transmitted in the downlink
-- direction but could not due to insufficient resources (e.g. buffer
-- memory), layer 2 congestion, or some other transmittal problem.
--
rbnEpsuS1uGtp       OBJECT IDENTIFIER ::= { rbnEpsuStatMIBObjects 1 }

rbnEpsuS1uDlPktsSent  OBJECT-TYPE
    SYNTAX      Counter64
    UNITS       "Packets"
    MAX-ACCESS  read-only
    STATUS      current
    DESCRIPTION
        "Total number of downlink GTP payload packets sent to eNodeBs
        over the S1-U interface."
    ::= { rbnEpsuS1uGtp 1 }

rbnEpsuS1uDlOctetsSent  OBJECT-TYPE
    SYNTAX      Counter64
    UNITS       "Octets"
    MAX-ACCESS  read-only
    STATUS      current
    DESCRIPTION
        "Total number of octets in downlink GTP payload packets sent to
        eNodeBs over the S1-U interface."
    ::= { rbnEpsuS1uGtp 2 }

rbnEpsuS1uDlPktsDropped  OBJECT-TYPE
    SYNTAX      Counter64
    UNITS       "Packets"
    MAX-ACCESS  read-only
    STATUS      current
    DESCRIPTION
        "Total number of downlink GTP payload packets dropped
        that should have been sent to eNodeBs over the S1-U interface."
    ::= { rbnEpsuS1uGtp 3 }

rbnEpsuS1uDlPolicingPktsDropped  OBJECT-TYPE
    SYNTAX      Counter64
    UNITS       "Packets"
    MAX-ACCESS  read-only
    STATUS      current
    DESCRIPTION
        "Total number of downlink GTP payload packets dropped due to
        MBR policing that should have been sent to eNodeBs over the
        S1-U interface."
    ::= { rbnEpsuS1uGtp 4 }

rbnEpsuS1uDlUeIdlePktsDropped  OBJECT-TYPE
    SYNTAX      Counter64
    UNITS       "Packets"
    MAX-ACCESS  read-only
    STATUS      current
    DESCRIPTION
        "Total number of downlink GTP payload packets which should
        have been sent to eNodeBs over the S1-U interface but were dropped
        due to UE in the idle mode, or the buffer has become full, or the UE
        has not been activated in a timely manner."
    ::= { rbnEpsuS1uGtp 5 }

rbnEpsuS1uUlPktsRcvd  OBJECT-TYPE
    SYNTAX      Counter64
    UNITS       "Packets"
    MAX-ACCESS  read-only
    STATUS      current
    DESCRIPTION
        "Total number of uplink GTP payload packets received
        from eNodeBs over the S1-U interface"
    ::= { rbnEpsuS1uGtp 6 }

rbnEpsuS1uUlOctetsRcvd  OBJECT-TYPE
    SYNTAX      Counter64
    UNITS       "Octets"
    MAX-ACCESS  read-only
    STATUS      current
    DESCRIPTION
        "Total number of octets in uplink GTP payload packets
        received from eNodeBs over the S1-U interface."
    ::= { rbnEpsuS1uGtp 7 }

rbnEpsuS1uUlPktsDiscarded  OBJECT-TYPE
    SYNTAX      Counter64
    UNITS       "Packets"
    MAX-ACCESS  read-only
    STATUS      current
    DESCRIPTION
        "Total number of discarded uplink payload GTP packets
        received from eNodeBs over the S1-U interface."
    ::= { rbnEpsuS1uGtp 8 }

rbnEpsuS1uUlBearerPktsDiscarded  OBJECT-TYPE
    SYNTAX      Counter64
    UNITS       "Packets"
    MAX-ACCESS  read-only
    STATUS      current
    DESCRIPTION
        "Total number of uplink payload GTP packets received from
        eNodeBs over the S1-U interface that were discarded due to
        bearer validation failure."
    ::= { rbnEpsuS1uGtp 9 }

rbnEpsuS1uUlPolicingPktsDiscarded  OBJECT-TYPE
    SYNTAX      Counter64
    UNITS       "Packets"
    MAX-ACCESS  read-only
    STATUS      current
    DESCRIPTION
        "Total number of uplink GTP payload packets received from
        eNodeBs over the S1-U interface that were discarded due to
        MBR policing."
    ::= { rbnEpsuS1uGtp 10 }

--
-- The rbnEpsuSgwGtp counter group will count all GTP tunnel packets
-- containing user payload data that are sent and received by the SGW on the
-- GTP based S5/S8 interface. The byte counters include the total packet
-- length which is defined as (tunnel IP header + GTP header + user
-- data IP packet).  Discarded packets are those received in the downlink
-- direction that have errors in the tunnel IP header, GTP header, or
-- there are insufficient resources (e.g. buffer memory) and the packet
-- cannot be processed further.  Dropped packets are those which were supposed
-- to be transmitted in the uplink direction but could not due to
-- insufficient resources (e.g. buffer memory), layer 2 congestion, or some
-- other transmittal problem.
--
rbnEpsuSgwGtp OBJECT IDENTIFIER ::= { rbnEpsuStatMIBObjects 2 }

rbnEpsuS5S8GtpDlPktsRcvd  OBJECT-TYPE
    SYNTAX      Counter64
    UNITS       "Packets"
    MAX-ACCESS  read-only
    STATUS      current
    DESCRIPTION
       "Total number of downlink GTP payload packets received
       from the PGW over the S5/S8 interface."
    ::= { rbnEpsuSgwGtp 1 }

rbnEpsuS5S8GtpDlOctetsRcvd  OBJECT-TYPE
    SYNTAX      Counter64
    UNITS       "Octets"
    MAX-ACCESS  read-only
    STATUS      current
    DESCRIPTION
       "Total number of octets in downlink GTP payload packets
       received from the PGW over the S5/S8 interface."
    ::= { rbnEpsuSgwGtp 2 }

rbnEpsuS5S8GtpDlPktsDiscarded  OBJECT-TYPE
    SYNTAX      Counter64
    UNITS       "Packets"
    MAX-ACCESS  read-only
    STATUS      current
    DESCRIPTION
       "Total number of discarded downlink GTP payload packets
       received from the PGW over the S5/S8 interface."
    ::= { rbnEpsuSgwGtp 3 }

rbnEpsuS5S8GtpUlPktsSent  OBJECT-TYPE
    SYNTAX      Counter64
    UNITS       "Packets"
    MAX-ACCESS  read-only
    STATUS      current
    DESCRIPTION
       "Total number of uplink GTP payload packets sent
       tp the PGW over the S5/S8 interface."
    ::= { rbnEpsuSgwGtp 4 }

rbnEpsuS5S8GtpUlOctetsSent  OBJECT-TYPE
    SYNTAX      Counter64
    UNITS       "Octets"
    MAX-ACCESS  read-only
    STATUS      current
    DESCRIPTION
       "Total number of octets in uplink GTP payload packets
       sent to the PGW over the S5/S8 interface."
    ::= { rbnEpsuSgwGtp 5 }

rbnEpsuS5S8GtpUlPktsDropped  OBJECT-TYPE
    SYNTAX      Counter64
    UNITS       "Packets"
    MAX-ACCESS  read-only
    STATUS      current
    DESCRIPTION
       "Total number of dropped uplink GTP payload packets that
       should have been sent to the PGW over the S5/S8 interface."
    ::= { rbnEpsuSgwGtp 6 }

--
-- The rbnEpsuPgwGtp counter group will count all GTP tunnel packets
-- containing user payload data that are sent or received by the PDN Gateway
-- (PGW) on the GTP based S5/S8 interface. The byte counters total include the
-- packet length which is defined as (tunnel IP header + GTP header +
-- user data IP packet).  Discarded packets are those received in the uplink
-- direction that have errors in the tunnel IP header, GTP header, or
-- there are insufficient resources (e.g. buffer memory) and the packet
-- cannot be processed further.  Dropped packets are those which were
-- supposed to be transmitted in the downlink direction but could not due to
-- insufficient resources (e.g. buffer memory), layer 2 congestion, or some
-- other transmittal problem.
--
rbnEpsuPgwGtp OBJECT IDENTIFIER ::= { rbnEpsuStatMIBObjects 3 }

rbnEpsuS5S8GtpDlPktsSent  OBJECT-TYPE
    SYNTAX      Counter64
    UNITS       "Packets"
    MAX-ACCESS  read-only
    STATUS      current
    DESCRIPTION
       "Total number of downlink GTP payload packets sent to
       SGW over the S5/S8 interface."
    ::= { rbnEpsuPgwGtp 1 }

rbnEpsuS5S8GtpDlOctetsSent  OBJECT-TYPE
    SYNTAX      Counter64
    UNITS       "Octets"
    MAX-ACCESS  read-only
    STATUS      current
    DESCRIPTION
       "Total number of octets in downlink GTP payload packets
       sent to SGW over the S5/S8 interface."
    ::= { rbnEpsuPgwGtp 2 }

rbnEpsuS5S8GtpDlPktsDropped  OBJECT-TYPE
    SYNTAX      Counter64
    UNITS       "Packets"
    MAX-ACCESS  read-only
    STATUS      current
    DESCRIPTION
       "Total number of dropped downlink GTP payload packets
       that should have been sent to SGW over the S5/S8 interface."
    ::= { rbnEpsuPgwGtp 3 }

rbnEpsuS5S8GtpDlPolicingPktsDropped  OBJECT-TYPE
    SYNTAX      Counter64
    UNITS       "Packets"
    MAX-ACCESS  read-only
    STATUS      current
    DESCRIPTION
       "Total number of downlink GTP payload packets dropped due
       to MBR policing that should have been sent to SGW over
       the S5/S8 interface."
    ::= { rbnEpsuPgwGtp 4 }

rbnEpsuS5S8GtpUlPktsRcvd  OBJECT-TYPE
    SYNTAX      Counter64
    UNITS       "Packets"
    MAX-ACCESS  read-only
    STATUS      current
    DESCRIPTION
       "Total number of uplink GTP payload packets received from
       SGW over the S5/S8 interface."
    ::= { rbnEpsuPgwGtp 5 }

rbnEpsuS5S8GtpUlOctetsRcvd OBJECT-TYPE
    SYNTAX      Counter64
    UNITS       "Octets"
    MAX-ACCESS  read-only
    STATUS      current
    DESCRIPTION
       "Total number of octets in uplink GTP payload packets
       received from SGW over the S5/S8 interface."
    ::= { rbnEpsuPgwGtp 6 }

rbnEpsuS5S8GtpUlPktsDiscarded OBJECT-TYPE
    SYNTAX      Counter64
    UNITS       "Packets"
    MAX-ACCESS  read-only
    STATUS      current
    DESCRIPTION
       "Total number of discarded uplink GTP payload packets
       received from SGW over the S5/S8 interface."
    ::= { rbnEpsuPgwGtp 7 }

rbnEpsuS5S8GtpUlBearerPktsDiscarded OBJECT-TYPE
    SYNTAX      Counter64
    UNITS       "Packets"
    MAX-ACCESS  read-only
    STATUS      current
    DESCRIPTION
       "Total number of uplink GTP payload packets received from
       SGW over the S5/S8 interface that were discarded due to
       bearer validation failure."
    ::= { rbnEpsuPgwGtp 8 }

rbnEpsuS5S8GtpUlPolicingPktsDiscarded OBJECT-TYPE
    SYNTAX      Counter64
    UNITS       "Packets"
    MAX-ACCESS  read-only
    STATUS      current
    DESCRIPTION
       "Total number of uplink GTP payload packets received from
       SGW over the S5/S8 interface that were discarded due to
       MBR policiing."
    ::= { rbnEpsuPgwGtp 9 }

--
-- The rbnEpsuSgi counter group will count all data packet that are
-- sent or received over the SGi interface.  The packets are not tunneled
-- by the PGW so the total length simply includes the IP packet length.
-- Discarded packets those received in the downlink direction when there are
-- insufficient resources (e.g. buffer memory) and the packet cannot
-- be processed further.  Dropped packets are those which were supposed
-- to be transmitted in the uplink direction but could not due to insufficient
-- resources (e.g. buffer memory), layer 2 congestion, or some other
-- transmittal problem.
--
rbnEpsuSgi OBJECT IDENTIFIER ::= { rbnEpsuStatMIBObjects 4 }

rbnEpsuSgiDlPktsRcvd  OBJECT-TYPE
    SYNTAX      Counter64
    UNITS       "Packets"
    MAX-ACCESS  read-only
    STATUS      current
    DESCRIPTION
       "Total number of downlink user payload packets received
       over the SGi interface."
    ::= { rbnEpsuSgi 1 }

rbnEpsuSgiDlOctetsRcvd  OBJECT-TYPE
    SYNTAX      Counter64
    UNITS       "Octets"
    MAX-ACCESS  read-only
    STATUS      current
    DESCRIPTION
       "Total number of octets in downlink user payload packets received
       over the SGi interface."
    ::= { rbnEpsuSgi 2 }

rbnEpsuSgiDlV6PktsRcvd  OBJECT-TYPE
    SYNTAX      Counter64
    UNITS       "Packets"
    MAX-ACCESS  read-only
    STATUS      current
    DESCRIPTION
       "Total number of downlink IPv6 user payload packets received
       over the SGi interface."
    ::= { rbnEpsuSgi 3 }

rbnEpsuSgiDlV6OctetsRcvd  OBJECT-TYPE
    SYNTAX      Counter64
    UNITS       "Octets"
    MAX-ACCESS  read-only
    STATUS      current
    DESCRIPTION
       "Total number of octets in downlink IPv6 user payload packets
       received over the SGi interface."
    ::= { rbnEpsuSgi 4 }

rbnEpsuSgiDlPktsDiscarded  OBJECT-TYPE
    SYNTAX      Counter64
    UNITS       "Packets"
    MAX-ACCESS  read-only
    STATUS      current
    DESCRIPTION
       "Total number of discarded downlink user payload packets
       received over the SGi interface."
    ::= { rbnEpsuSgi 5 }

rbnEpsuSgiUlPktsSent  OBJECT-TYPE
    SYNTAX      Counter64
    UNITS       "Packets"
    MAX-ACCESS  read-only
    STATUS      current
    DESCRIPTION
       "Total number of uplink user payload packets sent over
       the SGi interface."
    ::= { rbnEpsuSgi 6 }

rbnEpsuSgiUlOctetsSent  OBJECT-TYPE
    SYNTAX      Counter64
    UNITS       "Octets"
    MAX-ACCESS  read-only
    STATUS      current
    DESCRIPTION
       "Total number of octets in uplink user payload packets
       sent over the SGi interface."
    ::= { rbnEpsuSgi 7 }

rbnEpsuSgiUlV6PktsSent  OBJECT-TYPE
    SYNTAX      Counter64
    UNITS       "Packets"
    MAX-ACCESS  read-only
    STATUS      current
    DESCRIPTION
       "Total number of uplink IPv6 user payload packets sent over
       the SGi interface."
    ::= { rbnEpsuSgi 8 }

rbnEpsuSgiUlV6OctetsSent  OBJECT-TYPE
    SYNTAX      Counter64
    UNITS       "Octets"
    MAX-ACCESS  read-only
    STATUS      current
    DESCRIPTION
       "Total number of octets in uplink user payload packets
       sent over the SGi interface."
    ::= { rbnEpsuSgi 9 }

rbnEpsuSgiUlPktsDropped  OBJECT-TYPE
    SYNTAX      Counter64
    UNITS       "Packets"
    MAX-ACCESS  read-only
    STATUS      current
    DESCRIPTION
       "Total number of dropped uplink user payload packets that should
       have been sent over the SGi interface."
    ::= { rbnEpsuSgi 10 }

--
-- The rbnEpsuSgiApn counter group will count all data packet that are
-- sent or received over the SGi interface for each Access Point Name
-- (APN).  The packets are not tunneled by the PGW so the total length
-- simply includes the IP packet length.  Discarded packets are those received
-- in the downlink direction which cannot be processed further due to
-- insufficient resources (e.g. buffer memory).  Dropped packets are those
-- which were supposed to be transmitted in the uplink direction but could
-- not be due to insufficient resources (e.g. buffer memory), layer 2
-- congestion, or some other transmittal problem.
--
rbnEpsuSgiApn        OBJECT IDENTIFIER ::= { rbnEpsuStatMIBObjects 5 }

rbnEpsuSgiApnStatsTable    OBJECT-TYPE
    SYNTAX      SEQUENCE OF RbnEpsuSgiApnStatsEntry
    MAX-ACCESS  not-accessible
    STATUS      current
    DESCRIPTION
        "This table contains the user payload packet counters
        per Access Point Name (APN)."
    ::= { rbnEpsuSgiApn 1 }

rbnEpsuSgiApnStatsEntry     OBJECT-TYPE
    SYNTAX      RbnEpsuSgiApnStatsEntry
    MAX-ACCESS  not-accessible
    STATUS      current
    DESCRIPTION
        "The user payload packet counters for an APN."
    INDEX   { rbnEpsuSgiApnIndex }
    ::= { rbnEpsuSgiApnStatsTable 1 }

RbnEpsuSgiApnStatsEntry ::= SEQUENCE {
    rbnEpsuSgiApnIndex             Unsigned32,
    rbnEpsuSgiApnName              SnmpAdminString,
    rbnEpsuSgiApnDlPktsRcvd        Counter64,
    rbnEpsuSgiApnDlOctetsRcvd      Counter64,
    rbnEpsuSgiApnDlPktsDiscarded   Counter64,
    rbnEpsuSgiApnUlPktsSent        Counter64,
    rbnEpsuSgiApnUlOctetsSent      Counter64,
    rbnEpsuSgiApnUlPktsDropped     Counter64,
    rbnEpsuSgiApnDlV6PktsRcvd      Counter64,
    rbnEpsuSgiApnDlV6OctetsRcvd    Counter64,
    rbnEpsuSgiApnUlV6PktsSent      Counter64,
    rbnEpsuSgiApnUlV6OctetsSent    Counter64
}

rbnEpsuSgiApnIndex  OBJECT-TYPE
    SYNTAX      Unsigned32(1..4294967295)
    MAX-ACCESS  not-accessible
    STATUS      current
    DESCRIPTION
        "An integer value assigned to uniquely identify the entry."
    ::= { rbnEpsuSgiApnStatsEntry 1 }

rbnEpsuSgiApnName  OBJECT-TYPE
    SYNTAX      SnmpAdminString (SIZE(1..255))
    MAX-ACCESS  read-only
    STATUS      current
    DESCRIPTION
        "The access point name (APN) associated with rbnEpsuSgiApnIndex."
    ::= { rbnEpsuSgiApnStatsEntry 2 }

rbnEpsuSgiApnDlPktsRcvd  OBJECT-TYPE
    SYNTAX      Counter64
    UNITS       "Packets"
    MAX-ACCESS  read-only
    STATUS      current
    DESCRIPTION
        "Total number of downlink user payload packets received
        over the SGi interface for the APN."
    ::= { rbnEpsuSgiApnStatsEntry 3 }

rbnEpsuSgiApnDlOctetsRcvd  OBJECT-TYPE
    SYNTAX      Counter64
    UNITS       "Octets"
    MAX-ACCESS  read-only
    STATUS      current
    DESCRIPTION
        "Total number of octets in downlink user payload packets
        received over the SGi interface for the APN."
    ::= { rbnEpsuSgiApnStatsEntry 4 }

rbnEpsuSgiApnDlPktsDiscarded  OBJECT-TYPE
    SYNTAX      Counter64
    UNITS       "Packets"
    MAX-ACCESS  read-only
    STATUS      current
    DESCRIPTION
        "Total number of discarded downlink user payload packets
        received over the SGi interface for the APN."
    ::= { rbnEpsuSgiApnStatsEntry 5 }

rbnEpsuSgiApnUlPktsSent  OBJECT-TYPE
    SYNTAX      Counter64
    UNITS       "Packets"
    MAX-ACCESS  read-only
    STATUS      current
    DESCRIPTION
        "Total number of uplink user payload packets sent
        over the SGi interface for the APN."
    ::= { rbnEpsuSgiApnStatsEntry 6 }

rbnEpsuSgiApnUlOctetsSent  OBJECT-TYPE
    SYNTAX      Counter64
    UNITS       "Octets"
    MAX-ACCESS  read-only
    STATUS      current
    DESCRIPTION
        "Total number of octets in uplink user payload packets
        sent over the SGi interface for the APN."
    ::= { rbnEpsuSgiApnStatsEntry 7 }

rbnEpsuSgiApnUlPktsDropped  OBJECT-TYPE
    SYNTAX      Counter64
    UNITS       "Packets"
    MAX-ACCESS  read-only
    STATUS      current
    DESCRIPTION
        "Total number of dropped uplink payload GTP packets
        that should have been sent over the SGi interface for the APN."
    ::= { rbnEpsuSgiApnStatsEntry 8 }

rbnEpsuSgiApnDlV6PktsRcvd  OBJECT-TYPE
    SYNTAX      Counter64
    UNITS       "Packets"
    MAX-ACCESS  read-only
    STATUS      current
    DESCRIPTION
        "Total number of downlink IPv6 user payload packets received
        over the SGi interface for the APN."
    ::= { rbnEpsuSgiApnStatsEntry 9 }

rbnEpsuSgiApnDlV6OctetsRcvd  OBJECT-TYPE
    SYNTAX      Counter64
    UNITS       "Octets"
    MAX-ACCESS  read-only
    STATUS      current
    DESCRIPTION
        "Total number of octets in downlink IPv6 user payload packets
        received over the SGi interface for the APN."
    ::= { rbnEpsuSgiApnStatsEntry 10 }

rbnEpsuSgiApnUlV6PktsSent  OBJECT-TYPE
    SYNTAX      Counter64
    UNITS       "Packets"
    MAX-ACCESS  read-only
    STATUS      current
    DESCRIPTION
        "Total number of uplink IPv6 user payload packets sent
        over the SGi interface for the APN."
    ::= { rbnEpsuSgiApnStatsEntry 11 }

rbnEpsuSgiApnUlV6OctetsSent  OBJECT-TYPE
    SYNTAX      Counter64
    UNITS       "Octets"
    MAX-ACCESS  read-only
    STATUS      current
    DESCRIPTION
        "Total number of octets in uplink IPv6 user payload packets
        sent over the SGi interface for the APN."
    ::= { rbnEpsuSgiApnStatsEntry 12 }


--
-- Notification Group
--      must have 0 - for v1/v2/v3 compatibility
rbnEpsuNotifcationGroup OBJECT IDENTIFIER ::= { rbnEpsuMIB 0 }


--
-- Conformance & Compliance
--
rbnEpsuMIBConformance   OBJECT IDENTIFIER ::= { rbnEpsuMIB 2 }
rbnEpsuMIBGroups        OBJECT IDENTIFIER ::= { rbnEpsuMIBConformance 1 }
rbnEpsuMIBCompliances   OBJECT IDENTIFIER ::= { rbnEpsuMIBConformance 2 }

rbnEpsuS1uGtpGroup  OBJECT-GROUP
    OBJECTS {
        rbnEpsuS1uDlPktsSent,
        rbnEpsuS1uDlOctetsSent,
        rbnEpsuS1uDlPktsDropped,
        rbnEpsuS1uDlPolicingPktsDropped,
        rbnEpsuS1uDlUeIdlePktsDropped,
        rbnEpsuS1uUlPktsRcvd,
        rbnEpsuS1uUlOctetsRcvd,
        rbnEpsuS1uUlPktsDiscarded,
        rbnEpsuS1uUlBearerPktsDiscarded,
        rbnEpsuS1uUlPolicingPktsDiscarded
    }
    STATUS     current
    DESCRIPTION
        "This object group contains counters for GTP
        on the S1-U interface"
    ::= { rbnEpsuMIBGroups 1 }

rbnEpsuSgwGtpGroup OBJECT-GROUP
    OBJECTS {
        rbnEpsuS5S8GtpDlPktsRcvd,
        rbnEpsuS5S8GtpDlOctetsRcvd,
        rbnEpsuS5S8GtpDlPktsDiscarded,
        rbnEpsuS5S8GtpUlPktsSent,
        rbnEpsuS5S8GtpUlOctetsSent,
        rbnEpsuS5S8GtpUlPktsDropped
    }
    STATUS     current
    DESCRIPTION
        "This object group contains counters for GTP
        on the S5/S8 SGW inteface "
    ::= { rbnEpsuMIBGroups 2 }

rbnEpsuPgwGtpGroup OBJECT-GROUP
    OBJECTS {
        rbnEpsuS5S8GtpDlPktsSent,
        rbnEpsuS5S8GtpDlOctetsSent,
        rbnEpsuS5S8GtpDlPktsDropped,
        rbnEpsuS5S8GtpDlPolicingPktsDropped,
        rbnEpsuS5S8GtpUlPktsRcvd,
        rbnEpsuS5S8GtpUlOctetsRcvd,
        rbnEpsuS5S8GtpUlPktsDiscarded,
        rbnEpsuS5S8GtpUlBearerPktsDiscarded,
        rbnEpsuS5S8GtpUlPolicingPktsDiscarded
    }
    STATUS     current
    DESCRIPTION
        "This object group contains counters for GTP
        on the S5/S8 PGW inteface"
    ::= { rbnEpsuMIBGroups 3 }

rbnEpsuSgiGroup OBJECT-GROUP
    OBJECTS {
        rbnEpsuSgiDlPktsRcvd,
        rbnEpsuSgiDlOctetsRcvd,
        rbnEpsuSgiDlV6PktsRcvd,
        rbnEpsuSgiDlV6OctetsRcvd,
        rbnEpsuSgiDlPktsDiscarded,
        rbnEpsuSgiUlPktsSent,
        rbnEpsuSgiUlOctetsSent,
        rbnEpsuSgiUlPktsDropped,
        rbnEpsuSgiUlV6PktsSent,
        rbnEpsuSgiUlV6OctetsSent
    }
    STATUS     current
    DESCRIPTION
        "This object group contains counters for SGi inteface."
    ::= { rbnEpsuMIBGroups 4 }

rbnEspuSgiApnGroup  OBJECT-GROUP
    OBJECTS {
        rbnEpsuSgiApnName,
        rbnEpsuSgiApnDlPktsRcvd,
        rbnEpsuSgiApnDlOctetsRcvd,
        rbnEpsuSgiApnDlV6PktsRcvd,
        rbnEpsuSgiApnDlV6OctetsRcvd,
        rbnEpsuSgiApnDlPktsDiscarded,
        rbnEpsuSgiApnUlPktsSent,
        rbnEpsuSgiApnUlOctetsSent,
        rbnEpsuSgiApnUlV6PktsSent,
        rbnEpsuSgiApnUlV6OctetsSent,
        rbnEpsuSgiApnUlPktsDropped
    }
    STATUS     current
    DESCRIPTION
        "This object group contains counters for user payload
        packets per APN received on the SGi interface"
    ::= { rbnEpsuMIBGroups 5 }

rbnEpsuMIBCompliance  MODULE-COMPLIANCE
    STATUS     current
    DESCRIPTION
        "The compliance statement for SNMP entities which support
         EPSU statistics"
    MODULE
        GROUP rbnEpsuS1uGtpGroup
        DESCRIPTION
            "This group is mandatory if the S1U interface is supported
            on SGW."

        GROUP rbnEpsuSgwGtpGroup
        DESCRIPTION
            "This group is mandatory if S5/S8 interface is supported
            on SGW."

        GROUP rbnEpsuPgwGtpGroup
        DESCRIPTION
            "This group is mandatory if S5/S8 interface is supported
            on PGW."

        GROUP rbnEpsuSgiGroup
        DESCRIPTION
            "This group is mandatory if SGi interface is supported on
            PGW."

        GROUP rbnEspuSgiApnGroup
        DESCRIPTION
            "This group is mandatory if APN is supported."

    ::= { rbnEpsuMIBCompliances 1 }

END
