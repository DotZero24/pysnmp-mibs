--
-- The Ericsson top-level Textual Conventions MIB
--
-- Copyright (c) 2008 by Ericsson AB.
-- All rights reserved.
--
-- This MIB is documented further in EAB/OP-07:0139
--
-- Authors:
-- Stefan Wallin (DataDuctus, primary author)
-- Vincent Desbois
-- Ulf Hallgarn
-- Tomas Jonsson
-- Peter Loborg
-- David Partain
-- Mattias Pettersson A
-- Ingemar Segerberg
-- Johan Wallin
-- Martin Wettergren
--

ERICSSON-TC-MIB DEFINITIONS ::= BEGIN

-- Add further imports as needed
IMPORTS
        MODULE-IDENTITY
                FROM SNMPv2-SMI
        TEXTUAL-CONVENTION
                FROM SNMPv2-TC
        ericssonModules
                FROM ERICSSON-TOP-MIB;


ericssonTCMIB MODULE-IDENTITY
        LAST-UPDATED "200810170000Z"
        ORGANIZATION "Ericsson AB"
        CONTACT-INFO
                "Email: snmp.mib.contact@ericsson.com "
        DESCRIPTION
                "This MIB document includes textual conventions
                that can be used by all of the Ericsson group.
                The intention is to have shared definitions such
                that integration and SNMP development are made
                easier.

                Document number: 2/196 03-CXC 172 7549, Rev A"
        REVISION      "200810170000Z"
        DESCRIPTION
                "Initial version of this MIB module."
        ::= { ericssonModules 1 }

--=======================
--==Textual conventions==
--=======================

EriMO ::= TEXTUAL-CONVENTION
        DISPLAY-HINT "1a"
        STATUS current
        DESCRIPTION
                "The 3GPP naming convention shall be used as the
                format for the managed object parameter.  Note
                that the granularity MUST be sufficient to
                guarantee unique alarm states and relevant
                resource identification to the operator.  NOTE:
                The DN should be *relative* to the node's *own*
                root."
        REFERENCE
                "3GPP TS 32.106-8 V3.2, Name convention for
                Managed Objects"
        SYNTAX OCTET STRING(SIZE(4..150))
END
