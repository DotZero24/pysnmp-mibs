GBNPlatformOAMSsh-MIB DEFINITIONS ::= BEGIN

    IMPORTS
        MODULE-IDENTITY, OBJECT-TYPE,
        Counter32, Gauge32,
        Unsigned32, Integer32,
        IpAddress, NOTIFICATION-TYPE            FROM SNMPv2-SMI

        RowStatus, TruthValue,
        DisplayString, MacAddress               FROM SNMPv2-TC

        MODULE-COMPLIANCE, OBJECT-GROUP         FROM SNMPv2-CONF

        snmpTraps                               FROM SNMPv2-MIB

        gbnPlatformOAM                          FROM GBNPlatformOAM-MIB;

    gbnPlatformOAMSsh  MODULE-IDENTITY
        LAST-UPDATED    "0505250000Z"  -- May 25, 2005
        ORGANIZATION    "Greentech"
        CONTACT-INFO    "Adam Armstrong
                         E-mail: adama@observium.org"

        DESCRIPTION     "Ssh mib definition."

        REVISION        "0505250000Z"  -- May 25, 2005
        DESCRIPTION     "Initial MIB creation."

        ::= { gbnPlatformOAM 11 }

    sshVersion OBJECT-TYPE
        SYNTAX INTEGER {
            v1(1),
            v2(2)
        }
        MAX-ACCESS read-only
        STATUS current
        DESCRIPTION
            "SSH version."
        ::= { gbnPlatformOAMSsh 1 }

    sshState OBJECT-TYPE
        SYNTAX INTEGER {
            enable(1),
            disable(2)
        }
        MAX-ACCESS read-write
        STATUS current
        DESCRIPTION
            "enable or disable SSH."
        ::= { gbnPlatformOAMSsh 2 }

    sshKeyAvailable OBJECT-TYPE
        SYNTAX INTEGER {
            available(1),
            unavailable(2)
        }
        MAX-ACCESS read-only
        STATUS current
        DESCRIPTION
            "SSH key file state."
        ::= { gbnPlatformOAMSsh 3 }

   END
