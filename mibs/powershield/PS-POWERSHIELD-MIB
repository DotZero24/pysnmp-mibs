PS-POWERSHIELD-MIB DEFINITIONS ::= BEGIN

--
-- This MIB is for PowerShield SNMP Adaptor Firmware Version 3.0.0.0
--

IMPORTS
    MODULE-IDENTITY,
    OBJECT-TYPE,
    Integer32,
    NOTIFICATION-TYPE,
    enterprises								FROM SNMPv2-SMI;

	-- ===============================================================================================
	-- Identity
	-- ===============================================================================================
    --define powerhsield enterprise root
    psPowerShield MODULE-IDENTITY
    LAST-UPDATED "201006100108Z"
	ORGANIZATION "PowerShield Limited"
	CONTACT-INFO "12 Target Place, Albany Auckland, New Zealand. Phone:+64 9 913 7576"
	DESCRIPTION "PowerShield Limited. Manufacturing Battery Monitoring Equipment"
	REVISION "201006100108Z"
	DESCRIPTION "MIB file to describe the B1001"
	::= { enterprises 35154 }

	-- ===============================================================================================
	-- top level structure
	-- ===============================================================================================
    psB1001 				OBJECT IDENTIFIER ::= { psPowerShield 1001 }
    psNotificationsObjects  OBJECT IDENTIFIER ::= { psB1001 1 }
	psNotifications			OBJECT IDENTIFIER ::= { psB1001 2 }
	psNotificationsPrefix	OBJECT IDENTIFIER ::= { psNotifications 0 }     -- TRAP reverse mappable
	psStrings 				OBJECT IDENTIFIER ::= { psB1001 3 }
	psMonoblocks 			OBJECT IDENTIFIER ::= { psB1001 4 }
	psDebuggingObjects 		OBJECT IDENTIFIER ::= { psB1001 5 }

	-- ===============================================================================================
	-- Notification Objects
	-- ===============================================================================================
	-- timestamp
    psAlarmTimeStamp OBJECT-TYPE
    	SYNTAX OCTET STRING(SIZE(13))
    	MAX-ACCESS accessible-for-notify
    	STATUS current
    	DESCRIPTION "Timestamp"
    	::= { psNotificationsObjects 11 }

	-- catagory
	psAlarmCatagory OBJECT-TYPE
		SYNTAX INTEGER {
			notTriggered(1),
			lowLimitExceeded(2),
			highLimitExceeded(3),
			lowLimitExceededInDischarge(4),
			highLimitDischarge(5),
			lowLimitExceededInCharge(6),
			highLimitCharge(7)
		}
		MAX-ACCESS accessible-for-notify
		STATUS current
		DESCRIPTION "Alarm Catagory"
		::= { psNotificationsObjects 12 }

	-- channel number
	psAlarmChannel OBJECT-TYPE
		SYNTAX Integer32 (1..16)
		MAX-ACCESS accessible-for-notify
		STATUS current
		DESCRIPTION "Channel Number"
		::= { psNotificationsObjects 13 }

     -- string number
     psAlarmString OBJECT-TYPE
     	SYNTAX Integer32 (1..16)
     	MAX-ACCESS accessible-for-notify
		STATUS current
		DESCRIPTION "String Number"
		::= { psNotificationsObjects 14 }

	-- monitor number
	psAlarmMonitor OBJECT-TYPE
		SYNTAX INTEGER {
			master(0),
			slave1(1),
			slave2(2),
			slave3(3),
			slave4(4),
			slave5(5),
			slave6(6),
			slave7(7),
			slave8(8),
			slave9(9),
			slave10(10),
			slave11(11),
			slave12(12),
			slave13(13),
			slave14(14),
			slave15(15)
		}
		MAX-ACCESS accessible-for-notify
		STATUS current
		DESCRIPTION "Monitor Number"
		::= { psNotificationsObjects 15 }

	-- monoblock number minimum
	psAlarmMonoblockMinimum OBJECT-TYPE
		SYNTAX Integer32 (0..1280)
		MAX-ACCESS accessible-for-notify
		STATUS current
		DESCRIPTION "Monoblock Number Start"
		::= { psNotificationsObjects 16 }

	-- monoblock number maximum
	psAlarmMonoblockMaximum OBJECT-TYPE
		SYNTAX Integer32 (0..1280)
		MAX-ACCESS accessible-for-notify
		STATUS current
		DESCRIPTION "Monoblock Number Stop"
		::= { psNotificationsObjects 17 }

	-- minimum limit
	psAlarmMinimum OBJECT-TYPE
		SYNTAX Integer32 (-2147483648..2147483647)
		MAX-ACCESS read-only
		STATUS current
		DESCRIPTION "Minimum Limit"
		::= { psNotificationsObjects 18 }

	-- maximum limit
	psAlarmMaximum OBJECT-TYPE
		SYNTAX Integer32 (-2147483648..2147483647)
		MAX-ACCESS read-only
		STATUS current
		DESCRIPTION "Maximum Limit"
		::= { psNotificationsObjects 19 }

	-- Input number
	psAlarmInputNumber OBJECT-TYPE
		SYNTAX Integer32 (1..32)
		MAX-ACCESS accessible-for-notify
		STATUS current
		DESCRIPTION "Input Number"
		::= { psNotificationsObjects 20 }

	-- Input state
	psAlarmInputState OBJECT-TYPE
		SYNTAX Integer32 (0..1)
		MAX-ACCESS accessible-for-notify
		STATUS current
		DESCRIPTION "AInput State"
		::= { psNotificationsObjects 21 }

	-- ===============================================================================================
	-- Notification
	-- ===============================================================================================
	-- Monoblock voltage - chg/dis [psAlarmMonoblock1]
	psAlarmMonoblockChargeDischarge NOTIFICATION-TYPE
		OBJECTS {
			psAlarmTimeStamp,
			psAlarmCatagory,
			psAlarmString,
			psAlarmMonitor,
			psAlarmChannel,
			psAlarmMonoblockMinimum,
			psAlarmMinimum,
			psAlarmMaximum
		}
		STATUS current
		DESCRIPTION "Monoblock voltage - charge/discharge"
		::= { psNotificationsPrefix 1 }

	-- Monoblock voltage - float [psAlarmMonoblock2]
	psAlarmMonoblockFloat NOTIFICATION-TYPE
		OBJECTS {
			psAlarmTimeStamp,
			psAlarmCatagory,
			psAlarmString,
			psAlarmMonitor,
			psAlarmChannel,
			psAlarmMonoblockMinimum,
			psAlarmMinimum,
			psAlarmMaximum
		}
		STATUS current
		DESCRIPTION "Monoblock voltage - float"
		::= { psNotificationsPrefix 2 }

	-- Monoblock voltage - variation [psAlarmMonoblock3]
	psAlarmMonoblockVoltageVariation NOTIFICATION-TYPE
		OBJECTS {
			psAlarmTimeStamp,
			psAlarmCatagory,
			psAlarmString,
			psAlarmMonoblockMinimum,
			psAlarmMonoblockMaximum,
			psAlarmMaximum
		}
		STATUS current
		DESCRIPTION "Monoblock voltage - variation"
		::= { psNotificationsPrefix 3 }

	-- Monoblock voltage - idle	[psAlarmMonoblock4]
	psAlarmMonoblockVoltageIdle NOTIFICATION-TYPE
		OBJECTS {
			psAlarmTimeStamp,
			psAlarmCatagory,
			psAlarmString,
			psAlarmMonitor,
			psAlarmMonoblockMinimum,
			psAlarmMaximum
		}
		STATUS current
		DESCRIPTION "Monoblock voltage - idle"
		::= { psNotificationsPrefix 4 }

	--String voltage - Charge / Discharge [psAlarmString1]
	psAlarmStringVoltageChargeDischarge NOTIFICATION-TYPE
		OBJECTS {
			psAlarmTimeStamp,
			psAlarmCatagory,
			psAlarmString,
			psAlarmMinimum,
			psAlarmMaximum
		}
		STATUS current
		DESCRIPTION "String voltage - Charge / Discharge"
		::= { psNotificationsPrefix 5 }

	-- String voltage - Float [psAlarmString2]
	psAlarmStringVoltageFloat NOTIFICATION-TYPE
		OBJECTS {
			psAlarmTimeStamp,
			psAlarmCatagory,
			psAlarmString,
			psAlarmMinimum,
			psAlarmMaximum
		}
		STATUS current
		DESCRIPTION "String voltage - Float"
		::= { psNotificationsPrefix 6 }

	-- ==========================================================================
	-- Charge current [psAlarmCurrent1]
	psAlarmChargeCurrent NOTIFICATION-TYPE
		OBJECTS {
			psAlarmTimeStamp,
			psAlarmCatagory,
			psAlarmString,
			psAlarmMonitor,
			psAlarmChannel,
			psAlarmMinimum,
			psAlarmMaximum
		}
		STATUS current
		DESCRIPTION "Charge Current"
		::= { psNotificationsPrefix 7 }

	-- Discharge current [psAlarmCurrent2]
	psAlarmDischargeCurrent NOTIFICATION-TYPE
		OBJECTS {
			psAlarmTimeStamp,
			psAlarmCatagory,
			psAlarmString,
			psAlarmMonitor,
			psAlarmChannel,
			psAlarmMinimum,
			psAlarmMaximum
		}
		STATUS current
		DESCRIPTION "Discharge Current"
		::= { psNotificationsPrefix 8 }

	-- Float current [psAlarmCurrent3]
	psAlarmFloatCurrent NOTIFICATION-TYPE
		OBJECTS {
			psAlarmTimeStamp,
			psAlarmCatagory,
			psAlarmString,
			psAlarmMonitor,
			psAlarmChannel,
			psAlarmMinimum,
			psAlarmMaximum
		}
		STATUS current
		DESCRIPTION "Float Current"
		::= { psNotificationsPrefix 9 }

	-- ==========================================================================
	-- String mode - charge [psAlarmStringEvent1]
	psAlarmStringModeCharge NOTIFICATION-TYPE
		OBJECTS {
			psAlarmTimeStamp,
			psAlarmString
		}
		STATUS current
		DESCRIPTION "String mode - Charge"
		::= { psNotificationsPrefix 10 }

	-- String mode - Discharge [psAlarmStringEvent2]
	psAlarmStringModeDischarge NOTIFICATION-TYPE
		OBJECTS {
			psAlarmTimeStamp,
			psAlarmString
		}
		STATUS current
		DESCRIPTION "String mode - Discharge"
		::= { psNotificationsPrefix 11 }

	-- String mode - Float [psAlarmStringEvent3]
	psAlarmStringModeFloat NOTIFICATION-TYPE
		OBJECTS {
			psAlarmTimeStamp,
			psAlarmString
		}
		STATUS current
		DESCRIPTION "String mode - Float"
		::= { psNotificationsPrefix 12 }

	-- String mode - Idle
	psAlarmStringModeIdle NOTIFICATION-TYPE
		OBJECTS {
			psAlarmTimeStamp,
			psAlarmString
		}
		STATUS current
		DESCRIPTION "String mode - Idle"
		::= { psNotificationsPrefix 13 }

	-- ==========================================================================
	-- Module failure [psAlarmSystem1]
	psAlarmModuleFailure NOTIFICATION-TYPE
		OBJECTS {
			psAlarmTimeStamp,
			psAlarmCatagory,
			psAlarmString,
			psAlarmMonitor,
			psAlarmMonoblockMinimum
		}
		STATUS current
		DESCRIPTION "Module failure"
		::= { psNotificationsPrefix 14 }

	-- Battery Monitor Offline [psAlarmSystem2]
	psAlarmMonitorOffline NOTIFICATION-TYPE
		OBJECTS {
			psAlarmTimeStamp,
			psAlarmCatagory,
			psAlarmMonitor
		}
		STATUS current
		DESCRIPTION "Battery monitor offline"
		::= { psNotificationsPrefix 15 }

	-- Memory Format [psAlarmSystem3]
	psAlarmMemoryFormat NOTIFICATION-TYPE
		OBJECTS {
			psAlarmTimeStamp,
			psAlarmMonitor
		}
		STATUS current
		DESCRIPTION "Memory format"
		::= { psNotificationsPrefix 16 }

	-- Memory Low [psAlarmSystem4]
	psAlarmMemoryLow NOTIFICATION-TYPE
		OBJECTS {
			psAlarmTimeStamp,
			psAlarmMonitor
		}
		STATUS current
		DESCRIPTION "Memory low"
		::= { psNotificationsPrefix 17 }

	-- Memory Full [psAlarmSystem5]
	psAlarmMemoryFull NOTIFICATION-TYPE
		OBJECTS {
			psAlarmTimeStamp,
			psAlarmMonitor
		}
		STATUS current
		DESCRIPTION "Memory Full"
		::= { psNotificationsPrefix 18 }

	-- Long term memory low [psAlarmSystem6]
	psAlarmLongTermMemoryLow NOTIFICATION-TYPE
		OBJECTS {
			psAlarmTimeStamp,
			psAlarmMonitor
		}
		STATUS current
		DESCRIPTION "Long term memory low"
		::= { psNotificationsPrefix 19 }

	-- Long term memory full [psAlarmSystem7]
	psAlarmLongTermMemoryFull NOTIFICATION-TYPE
		OBJECTS {
			psAlarmTimeStamp,
			psAlarmMonitor
		}
		STATUS current
		DESCRIPTION "Long term memory full"
		::= { psNotificationsPrefix 20 }
	-- ==========================================================================
	-- Temperature
	psAlarmTemperature NOTIFICATION-TYPE
		OBJECTS {
			psAlarmTimeStamp,
			psAlarmCatagory,
			psAlarmString,
			psAlarmMonitor,
			psAlarmChannel,
			psAlarmMinimum,
			psAlarmMaximum
		}
		STATUS current
		DESCRIPTION "Ambient Temperature"
		::= { psNotificationsPrefix 21 }

 	-- Monoblock post temperature
	psAlarmMonoblockPostTemperature NOTIFICATION-TYPE
		OBJECTS {
			psAlarmCatagory,
			psAlarmString,
			psAlarmMonoblockMinimum,
			psAlarmMinimum,
			psAlarmMaximum
		}
		STATUS current
		DESCRIPTION "Monoblock post temperature"
		::= { psNotificationsPrefix 22 }

 	-- Monoblock temperature variation
	psAlarmMonoblockTemperatureVariation NOTIFICATION-TYPE
		OBJECTS {
			psAlarmCatagory,
			psAlarmString,
			psAlarmMonoblockMinimum,
			psAlarmMaximum
		}
		STATUS current
		DESCRIPTION "Monoblock temperature variation"
		::= { psNotificationsPrefix 23 }

	--Monitored mains [psAlarmOther1]
	psAlarmMonitoredMains NOTIFICATION-TYPE
		OBJECTS {
			psAlarmTimeStamp
		}
		STATUS current
		DESCRIPTION "Monitored mains"
		::= { psNotificationsPrefix 24 }

	-- Comms notification [psAlarmOther2]
	psAlarmCommsNotification NOTIFICATION-TYPE
		OBJECTS {
			psAlarmTimeStamp
		}
		STATUS current
		DESCRIPTION "Comms notification"
		::= { psNotificationsPrefix 25 }

    -- Monoblock baseline impedance exceeded
    psAlarmBaselineImpedanceExceeded NOTIFICATION-TYPE
		OBJECTS {
			psAlarmTimeStamp,
			psAlarmCatagory,
			psAlarmString,
			psAlarmMonitor,
			psAlarmMonoblockMinimum,
			psAlarmMinimum,
			psAlarmMaximum
		}
		STATUS current
		DESCRIPTION "Monoblock baseline impedance exceeded"
		::= { psNotificationsPrefix 26 }

    -- String varaince impedance exceeded
    psAlarmStringVarianceImpedanceExceeded NOTIFICATION-TYPE
		OBJECTS {
			psAlarmTimeStamp,
			psAlarmCatagory,
			psAlarmString,
			psAlarmMonitor,
			psAlarmMonoblockMinimum,
			psAlarmMinimum,
			psAlarmMaximum
		}
		STATUS current
		DESCRIPTION "String varaince impedance exceeded"
		::= { psNotificationsPrefix 27 }

	-- Input alarm
	psAlarmInput NOTIFICATION-TYPE
		OBJECTS {
			psAlarmInputNumber,
			psAlarmInputState
		}
		STATUS current
		DESCRIPTION "Input Alarm"
		::= { psNotificationsPrefix 28 }

	-- ===============================================================================================
	-- String Table
	-- ===============================================================================================
	--string status table
	psStringTable OBJECT-TYPE
		SYNTAX SEQUENCE OF PsStringEntry
		MAX-ACCESS not-accessible
		STATUS current
		DESCRIPTION "String status table"
		::= { psStrings 1 }

	--table entry
	psStringEntry OBJECT-TYPE
		SYNTAX PsStringEntry
		MAX-ACCESS not-accessible
		STATUS current
		DESCRIPTION "String status table entry"
		INDEX { psStringNumber }
		::= { psStringTable 1 }

	--table elements
	PsStringEntry ::= SEQUENCE {
		psStringNumber			Integer32,
		psStringFirstMonoblock	Integer32,
		psStringLastMonoblock	Integer32,
		psStringState			OCTET STRING,
		psStringVoltage			Integer32,
		psStringTemperature		Integer32,
		psStringCurrent			Integer32,
		psStringTimestamp		OCTET STRING
	}

	--string number
	psStringNumber OBJECT-TYPE
		SYNTAX Integer32 (1..32)
		MAX-ACCESS not-accessible
		STATUS current
		DESCRIPTION "String Number"
		::= { psStringEntry 1 }

	--string first monoblock
	psStringFirstMonoblock OBJECT-TYPE
		SYNTAX Integer32 (1..1280)
		MAX-ACCESS read-only
		STATUS current
		DESCRIPTION "First Monoblock"
		::= { psStringEntry 2 }

	--string last monoblock
	psStringLastMonoblock OBJECT-TYPE
		SYNTAX Integer32 (1..1280)
		MAX-ACCESS read-only
		STATUS current
		DESCRIPTION "Last Monoblock"
		::= { psStringEntry 3 }

	--string state
	psStringState OBJECT-TYPE
		SYNTAX OCTET STRING(SIZE(0..12))
		MAX-ACCESS read-only
		STATUS current
		DESCRIPTION "String State"
		::= { psStringEntry 4 }

	--string voltage
	psStringVoltage OBJECT-TYPE
		SYNTAX Integer32 (0..2147483647)
		MAX-ACCESS read-only
		STATUS current
		DESCRIPTION "String Voltage (Volts x 10)"
		::= { psStringEntry 5 }

	--string temperature
	psStringTemperature OBJECT-TYPE
		SYNTAX Integer32 (0..65535)
		MAX-ACCESS read-only
		STATUS current
		DESCRIPTION "String Temperature (Degrees celsius x 10)"
		::= { psStringEntry 6 }

	--string current
	psStringCurrent OBJECT-TYPE
		SYNTAX Integer32 (0..65535)
		MAX-ACCESS read-only
		STATUS current
		DESCRIPTION "String Current"
		::= { psStringEntry 7 }

	--string timestamp
	psStringTimestamp OBJECT-TYPE
		SYNTAX OCTET STRING(SIZE(0..20))
		MAX-ACCESS read-only
		STATUS current
		DESCRIPTION "String Timestamp"
		::= { psStringEntry 8 }
	-- ===============================================================================================
	-- Monoblock Table
	-- ===============================================================================================
	--Monoblock voltage table
	psMonoblockTable OBJECT-TYPE
		SYNTAX SEQUENCE OF PsMonoblockEntry
		MAX-ACCESS not-accessible
		STATUS current
		DESCRIPTION "Monoblock voltage table"
		::= { psMonoblocks 1 }

	--table entry
	psMonoblockEntry OBJECT-TYPE
		SYNTAX PsMonoblockEntry
		MAX-ACCESS not-accessible
		STATUS current
		DESCRIPTION "Monoblock voltage table entry"
		INDEX { psMonoblockNumber }
		::= { psMonoblockTable 1 }

	--table elements
	PsMonoblockEntry ::= SEQUENCE {
		psMonoblockNumber		Integer32,
		psMonoblockOwner		Integer32,
		psMonoblockVoltage		Integer32,
		psMonoblockTemperature	Integer32,
		psMonoblockImpedance	Integer32,
		psMonoblockTimestamp	OCTET STRING
	}

	--monoblock number
	psMonoblockNumber OBJECT-TYPE
		SYNTAX Integer32 (1..1280)
		MAX-ACCESS not-accessible
		STATUS current
		DESCRIPTION "Monoblock number"
		::= { psMonoblockEntry 1 }

	--string number
	psMonoblockOwner OBJECT-TYPE
		SYNTAX Integer32 (1..1280)
		MAX-ACCESS read-only
		STATUS current
		DESCRIPTION "String number that the monoblock belongs to"
		::= { psMonoblockEntry 2 }

	--Monoblock voltage
	psMonoblockVoltage OBJECT-TYPE
		SYNTAX Integer32 (0..65535)
		MAX-ACCESS read-only
		STATUS current
		DESCRIPTION "Monoblock Voltage (mV)"
		::= { psMonoblockEntry 3 }

	--Monoblock temperature
	psMonoblockTemperature OBJECT-TYPE
		SYNTAX Integer32 (0..65535)
		MAX-ACCESS read-only
		STATUS current
		DESCRIPTION "Monoblock Temperature (Degrees celsius x 10)"
		::= { psMonoblockEntry 4 }

	--Monoblock impedance
	psMonoblockImpedance OBJECT-TYPE
		SYNTAX Integer32 (0..2147483647)
		MAX-ACCESS read-only
		STATUS current
		DESCRIPTION "Monoblock Impedance (uOhms)"
		::= { psMonoblockEntry 5 }

	--Monoblock timestamp
	psMonoblockTimestamp OBJECT-TYPE
		SYNTAX OCTET STRING(SIZE(0..20))
		MAX-ACCESS read-only
		STATUS current
		DESCRIPTION "Monoblock Timestamp"
		::= { psMonoblockEntry 6 }

	-- ===============================================================================================
	-- Debugging
	-- ===============================================================================================
	--Timeouts
	psDebuggingTimeouts OBJECT-TYPE
		SYNTAX Integer32 (0..65535)
		MAX-ACCESS read-only
		STATUS current
		DESCRIPTION "Number of serial timeouts"
		::= { psDebuggingObjects 1 }

	--Overflows
	psDebuggingOverflows OBJECT-TYPE
		SYNTAX Integer32 (0..65535)
		MAX-ACCESS read-only
		STATUS current
		DESCRIPTION "Number of serial overflows"
		::= { psDebuggingObjects 2 }

	--Total Packets Sent
	psDebuggingRequests OBJECT-TYPE
		SYNTAX Integer32 (0..65535)
		MAX-ACCESS read-only
		STATUS current
		DESCRIPTION "Total packets requested"
		::= { psDebuggingObjects 3 }

	--Total packets received
	psDebuggingResponses OBJECT-TYPE
		SYNTAX Integer32 (0..65535)
		MAX-ACCESS read-only
		STATUS current
		DESCRIPTION "Total response packets"
		::= { psDebuggingObjects 4 }


	--Valid packets
	psDebuggingValid OBJECT-TYPE
		SYNTAX Integer32 (0..65535)
		MAX-ACCESS read-only
		STATUS current
		DESCRIPTION "Total packets valid"
		::= { psDebuggingObjects 5 }

	--Invalid packets
	psDebuggingInvalid OBJECT-TYPE
		SYNTAX Integer32 (0..65535)
		MAX-ACCESS read-only
		STATUS current
		DESCRIPTION "Total packets invalid"
		::= { psDebuggingObjects 6 }

	--Retries
	psDebuggingRetries OBJECT-TYPE
		SYNTAX Integer32 (0..65535)
		MAX-ACCESS read-only
		STATUS current
		DESCRIPTION "Total retries send"
		::= { psDebuggingObjects 7 }

END
