-- SiteBoss 450 MIB

-- v 4.35 July 2 2013

-- Copyright (c) 2013 by Asentria Corporation.  All rights reserved.


SITEBOSS-450-STD-MIB DEFINITIONS ::= BEGIN

IMPORTS
 DisplayString
    FROM SNMPv2-TC
 IpAddress, TimeTicks, Integer32,
 MODULE-IDENTITY, NOTIFICATION-TYPE, OBJECT-TYPE
    FROM SNMPv2-SMI
 asentria
    FROM ASENTRIA-ROOT-MIB;

--***************************************************************************************
--MODULE IDENTITY
--***************************************************************************************

  s450 MODULE-IDENTITY
    LAST-UPDATED "201307020435Z"
    ORGANIZATION "Asentria Corporation"
    CONTACT-INFO
     "Phone:  206-344-8800
      Fax:    206-344-2116
      Email:  support@asentria.com"
    DESCRIPTION
      "MIB module for managing Asentria SiteBoss 450"

    REVISION      "201307020435Z"
    DESCRIPTION
      "-v4.35
       -Added snmpPoll objects (OMX-394).
       -Applicable since unit version 2.09.560."

    REVISION      "201305280434Z"
    DESCRIPTION
      "-v4.34
       -Fixed incorrect SYNTAX for sysCharMask (OMX-328).
       -Added evGlobal branch (OMX-228).
       -Applicable since unit version 2.09.500."

    REVISION      "201305100433Z"
    DESCRIPTION
      "-v4.33
       -Fixed incorrect SYNTAX statements for various objects (OMX-314).
       -Removed references to No Data events.
       -Applicable since unit version 2.09.380."

    REVISION      "201304100432Z"
    DESCRIPTION
      "-v4.32
       -Added non-weekly job scheduling objects (OMX-252).
       -Applicable since unit version 2.09.310."

    REVISION      "201303150431Z"
    DESCRIPTION
      "-v4.31
       -Renamed sysLocation branch to sysLoc (OMX-198).
       -Applicable since unit version 2.09.240."

    REVISION      "201303140430Z"
    DESCRIPTION
      "-v4.30
       -Added snmpProxy branch (OMX-190).
       -Applicable since unit version 2.09.280."

    REVISION      "201302060429Z"
    DESCRIPTION
      "-v4.29
       -Renamed telnet* objects.
       -Applicable since unit version 2.09.240."

    REVISION      "201301140428Z"
    DESCRIPTION
      "-v4.28
       -Added evReset branch and associated notification (OMX-83).
       -Applicable since unit version 2.09.220."

    REVISION      "201211190427Z"
    DESCRIPTION
      "-v4.27
       -Removed notification capture objects.
       -Added sysFileTransfer and sysUpdate objects. (BN 4632)
       -Added ethRouting objects.  (BN 4620)
       -Applicable since unit version 2.09.120."

    REVISION      "201208220426Z"
    DESCRIPTION
      "-v4.26
       -Added additional AC power monitor items."

    REVISION      "201208020425Z"
    DESCRIPTION
      "-v4.25
       -Removed non-weekly job schedule objects."

    REVISION      "201207090424Z"
    DESCRIPTION
      "-v4.24
       -Removed wirelessBand object."

    REVISION      "201207060423Z"
    DESCRIPTION
      "-v4.23
       -Added camera notification definition.
       -Updated comment for secUserConnectVia object."

    REVISION      "201206120422Z"
    DESCRIPTION
      "-v4.22
       -Removed user credentials objects."

    REVISION      "201205020421Z"
    DESCRIPTION
      "-v4.21
       -Added object for location.
       -Fixed objects for Generator Exercising Non-Start event."

    REVISION      "201204020420Z"
    DESCRIPTION
      "-v4.20
       -Revamped battery monitor objects."

    REVISION      "201203150419Z"
    DESCRIPTION
      "-v4.19
       -Added battery monitor status and config objects.
       -Added AC power monitor config objects."

    REVISION      "201202280418Z"
    DESCRIPTION
      "-v4.18
       -Fixed acpmsIndex range.
       -Added various objects for combined sensor status.
       -Changed meaning of esPointAliasValueStr for relay/power outputs."

    REVISION      "201202210417Z"
    DESCRIPTION
      "-v4.17
       -Removed genRunReqAsm object."

    REVISION      "201202200416Z"
    DESCRIPTION
      "-v4.16
       -Added objects for fuel sensor configuration; removed battery monitor status objects."

    REVISION      "201202140415Z"
    DESCRIPTION
      "-v4.15
       -Added objects for job scheduling, generator exercising, and battery monitor status."

    REVISION      "201202030904Z"
    DESCRIPTION
      "-v4.14
       -Added generatorNonStartTrap notification definition."

    REVISION      "201201160902Z"
    DESCRIPTION
      "-v4.13
       -Jumped to 4.xx Asentria version series.  The version 4
       series officially may improve compatibility with certain
       NMS installations by grouping all notifications in a
       dedicated branch.  No functional change from version 1.12."

    REVISION      "201112160900Z"
    DESCRIPTION
      "-v1.12
       -Added s450FuelSensorVolumeSuddenChangeTrap and
        s450FuelSensorVolumeSlowChangeTrap notification
        definitions."

    REVISION      "201112060900Z"
    DESCRIPTION
      "-v1.11
       -Moved notification definitions to dedicated branch."

    REVISION      "201112050900Z"
    DESCRIPTION
      "-v1.10
       -Added s450StockScriptTrap notification definition."

    REVISION      "201108080900Z"
    DESCRIPTION
      "-v1.09
       -Added s450StockOutputTrap notification definition."

    REVISION      "201108010900Z"
    DESCRIPTION
      "-v1.08
       -Added evMgmtReprocess object.
       -Added acPowerMonitorStatus branch."

    REVISION      "201107080900Z"
    DESCRIPTION
      "-v1.07
       -Added wirelessModemStatus branch.
       -Fixed bug where fuelSensorStatus branch was at the wrong object branch."

    REVISION      "201105180900Z"
    DESCRIPTION
      "-v1.06
       -Added s450FuelSensorVolumeTrap definition.
       -Added fuel sensor status objects."

    REVISION      "201104150900Z"
    DESCRIPTION
      "-v1.05
       -Removed reference to nonexistent data events."

    REVISION      "201101050900Z"
    DESCRIPTION
      "-v1.04
       -Added espcCCNormalThreshold object."

    REVISION      "201012020900Z"
    DESCRIPTION
      "-v1.03
       -Added esPointAliasValueStr object to simplify getting the
       current alias value of a CC input according to its current
       event state.
       -Added s450FuelSensorDisconnectTrap definition."

    REVISION      "201011030900Z"
    DESCRIPTION
      "-v1.02
       -Changed deadband, threshold, and current values for temperature
       sensors from integer to floating-point type.  This means the
       SNMP object type for the temperature settings (deadbands and
       thresholds) changed from Integer32 to DisplayString.
       -Fixed bug where SNMP integer range defined in the MIB for
       trapIncludedValue was 16-bit instead of 32-bit."

    REVISION      "201008240900Z"
    DESCRIPTION
      "-v1.01
       -Fixed bug where some stock traps had too few varbinds declared.
       -Removed useless trap definitions.
       -Corrected product number in comments for each declared object."

    REVISION      "201005170900Z"
    DESCRIPTION
      "-v1.00
       -Initial version"

    ::= { asentria 17 }
    --1.3.6.1.4.1.3052.17


--***************************************************************************************
--Concise MIB View: Top Level Branches
--***************************************************************************************

--  status                                 .1
--    eventSensorStatus                    .1.1
--      esPointTable                       .1.1.1
--    dataEventStatus                      .1.2
--      deStatusTable                      .1.2.1
--    fuelSensorStatus                     .1.6
--      fsStatusTable                      .1.6.1
--    wirelessModemStatus                  .1.7
--    acPowerMonitorStatus                 .1.8
--      acpmStatusTable                    .1.8.1
--    batteryMonitorStatus                 .1.10
--      bmStatusTable                      .1.10.1
--      bmJarStatusTable                   .1.10.2
--  config                                 .2
--    eventSensorBasics                    .2.1
--      esNumberEventSensors               .2.1.1
--      esTable                            .2.1.2
--      esNewSensors                       .2.1.3
--    eventSensorPointConfig               .2.2
--      esPointConfigTempTable             .2.2.1
--      esPointConfigCCTable               .2.2.2
--      esPointConfigHumidTable            .2.2.3
--      esPointConfigAITable               .2.2.5
--    serialPorts                          .2.3
--      numberPorts                        .2.3.1
--      portConfigTable                    .2.3.2
--    network                              .2.4
--      interface                          .2.4.1
--      defaultRouter                      .2.4.2
--      dnsTable                           .2.4.3
--      hostname                           .2.4.4
--      hostTable                          .2.4.5
--      ncpDuplex                          .2.4.6
--      ncpTimeout                         .2.4.7
--      snmp                               .2.4.8
--      ftpPush                            .2.4.9
--      routing                            .2.4.11
--      netSecurity                        .2.4.12
--      rts                                .2.4.13
--      trap                               .2.4.14
--      wireless                           .2.4.16
--      email                              .2.4.17
--      netAdvanced                        .2.4.18
--      web                                .2.4.19
--    time                                 .2.8
--      clock                              .2.8.1
--    console                              .2.10
--    unitSecurity                         .2.11
--      secCore                            .2.11.1
--      secUserTable                       .2.11.2
--      secFactory                         .2.11.3
--    event                                .2.12
--      evCore                             .2.12.1
--      evSched1                           .2.12.5
--      evSched2                           .2.12.6
--      evShskLowTable                     .2.12.7
--      evShskHighTable                    .2.12.8
--      evNoSensor                         .2.12.9
--      fuelSensor                         .2.12.11
--        fuelSensorGeneralTable           .2.12.11.1
--        fuelSensorTankTable              .2.12.11.2
--        fuelSensorCustomTankTable        .2.12.11.3
--        fuelSensorVolumeTable            .2.12.11.4
--        fuelSensorDisconnectTable        .2.12.11.5
--        fuelSensorSuddenChangeTable      .2.12.11.6
--        fuelSensorSlowChangeTable        .2.12.11.7
--      acPowerMonitor                     .2.12.12
--      batteryMonitor                     .2.12.14
--      evReset                            .2.12.16
--      evGlobal                           .2.12.18
--    action                               .2.14
--      actionSched                        .2.14.3
--      actionAsentria                     .2.14.4
--      actionHostTable                    .2.14.6
--      actionEmailTable                   .2.14.7
--      actionParseError                   .2.14.8
--    sys                                  .2.16
--      sysTime                            .2.16.1
--      sysPT                              .2.16.2
--      sysMTU                             .2.16.3
--      sysAnswerString                    .2.16.4
--      sysEventFileID                     .2.16.6
--      sysEscapeCharacter                 .2.16.7
--      sysTimeStamp                       .2.16.8
--      sysLog                             .2.16.9
--      sysCRDB                            .2.16.10
--      sysCharMask                        .2.16.11
--      sysPrompt                          .2.16.12
--      sysBootStatus                      .2.16.13
--      sysLoc                             .2.16.14
--      sysFileTransfer                    .2.16.17
--      sysUpdate                          .2.16.18
--    auditLog                             .2.17
--    scripting                            .2.18
--      scrGlobalEnable                    .2.18.1
--      scrDTRCtrlPortEnableTable          .2.18.2
--      scrTable                           .2.18.3
--      scrVolatileStringTable             .2.18.4
--      scrVolatileIntTable                .2.18.5
--      scrNonVolatileStringTable          .2.18.6
--      scrNonVolatileIntTable             .2.18.7
--    generator                            .2.19
--      genSet                             .2.19.1
--        genSetRelay                      .2.19.1.2
--        genSetCc                         .2.19.1.3
--      genRun                             .2.19.2
--        genRunNonstartEvent              .2.19.2.7
--    calendar                             .2.20
--  productIds                             .3
--    siteName                              3.1
--    thisProduct                          .3.2
--    stockTrapString                      .3.3
--    trapEventTypeNumber                  .3.4
--    trapEventTypeName                    .3.5
--    trapIncludedValue                    .3.6
--    trapIncludedString                   .3.7
--    trapTypeString                       .3.8
--    trapEventClassNumber                 .3.9
--    trapEventClassName                   .3.10
--  keyInterface                           .4.0

--***************************************************************************************
--Complete MIB View: All Objects
--***************************************************************************************

--  status                                           .1
--    eventSensorStatus                              .1.1
--      esPointTable                                 .1.1.1
--        esPointEntry                               .1.1.1.1
--          esIndexES                                .1.1.1.1.1
--          esIndexPC                                .1.1.1.1.2
--          esIndexPoint                             .1.1.1.1.3
--          esPointName                              .1.1.1.1.4
--          esPointInEventState                      .1.1.1.1.5
--          esPointValueInt                          .1.1.1.1.6
--          esPointValueStr                          .1.1.1.1.7
--          esPointTimeLastChange                    .1.1.1.1.8
--          esPointTimetickLastChange                .1.1.1.1.9
--          esPointAliasValueStr                     .1.1.1.1.10
--    dataEventStatus                                .1.2
--      deStatusTable                                .1.2.1
--        deStatusEntry                              .1.2.1.1
--          deStatusIndex                            .1.2.1.1.1
--          deStatusName                             .1.2.1.1.2
--          deStatusCounter                          .1.2.1.1.3
--          deStatusThreshold                        .1.2.1.1.4
--    fuelSensorStatus                               .1.6
--      fsStatusTable                                .1.6.1
--        fsStatusEntry                              .1.6.1.1
--          fsStatusIndex                            .1.6.1.1.1
--          fsStatusName                             .1.6.1.1.2
--          fsStatusDeviceState                      .1.6.1.1.3
--          fsStatusVolumeValueString                .1.6.1.1.4
--          fsStatusVolumePercentLevel               .1.6.1.1.7
--          fsStatusVolumeInEventState               .1.6.1.1.8
--          fsStatusCombined                         .1.6.1.1.9
--    wirelessModemStatus                            .1.7
--      wmsStatus                                    .1.7.1
--      wmsSignal                                    .1.7.2
--      wmsRSSI                                      .1.7.3
--      wmsBER                                       .1.7.4
--      wmsUpdated                                   .1.7.5
--      wmsRegistration                              .1.7.6
--      wmsLAC                                       .1.7.7
--      wmsCellID                                    .1.7.8
--      wmsIMSI                                      .1.7.9
--      wmsPhnum                                     .1.7.10
--      wmsLocalIP                                   .1.7.11
--      wmsMgfID                                     .1.7.12
--      wmsModelID                                   .1.7.13
--      wmsIMEI                                      .1.7.14
--      wmsRevID                                     .1.7.15
--      wmsNetName                                   .1.7.16
--      wmsGPRSStatus                                .1.7.17
--      wmsBand                                      .1.7.18
--      wmsChannel                                   .1.7.19
--      wmsCountryCode                               .1.7.20
--      wmsNetCode                                   .1.7.21
--      wmsPLMNColor                                 .1.7.22
--      wmsBScolor                                   .1.7.23
--      wmsMpRACH                                    .1.7.24
--      wmsMinRxLevel                                .1.7.25
--      wmsBaseCoeff                                 .1.7.26
--      wmsSIMStatus                                 .1.7.27
--      wmsICCID                                     .1.7.28
--      wmsModemType                                 .1.7.29
--    acPowerMonitorStatus                           .1.8
--      acpmStatusTable                              .1.8.1
--        acpmStatusEntry                            .1.8.1.1
--          acpmsIndex                               .1.8.1.1.1
--          acpmsName                                .1.8.1.1.2
--          acpmsAvgVoltageValueStr                  .1.8.1.1.3
--          acpmsAvgVoltageMinStr                    .1.8.1.1.4
--          acpmsAvgVoltageMaxStr                    .1.8.1.1.5
--          acpmsAvgVoltageAvgStr                    .1.8.1.1.6
--          acpmsAvgVoltageInEventState              .1.8.1.1.7
--          acpmsVoltagePhaseAValueStr               .1.8.1.1.8
--          acpmsVoltagePhaseBValueStr               .1.8.1.1.9
--          acpmsVoltagePhaseCValueStr               .1.8.1.1.10
--          acpmsAvgCurrentValueStr                  .1.8.1.1.11
--          acpmsAvgCurrentMinStr                    .1.8.1.1.12
--          acpmsAvgCurrentMaxStr                    .1.8.1.1.13
--          acpmsAvgCurrentAvgStr                    .1.8.1.1.14
--          acpmsAvgCurrentInEventState              .1.8.1.1.15
--          acpmsCurrentPhaseAValueStr               .1.8.1.1.16
--          acpmsCurrentPhaseBValueStr               .1.8.1.1.17
--          acpmsCurrentPhaseCValueStr               .1.8.1.1.18
--          acpmsFreqValueStr                        .1.8.1.1.19
--          acpmsFreqMinStr                          .1.8.1.1.20
--          acpmsFreqMaxStr                          .1.8.1.1.21
--          acpmsFreqAvgStr                          .1.8.1.1.22
--          acpmsFreqInEventState                    .1.8.1.1.23
--          acpmsTRPValueStr                         .1.8.1.1.24
--          acpmsTRPMinStr                           .1.8.1.1.25
--          acpmsTRPMaxStr                           .1.8.1.1.26
--          acpmsTRPAvgStr                           .1.8.1.1.27
--          acpmsTRPInEventState                     .1.8.1.1.28
--          acpmsRPPhaseAValueStr                    .1.8.1.1.29
--          acpmsRPPhaseBValueStr                    .1.8.1.1.30
--          acpmsRPPhaseCValueStr                    .1.8.1.1.31
--          acpmsCombined                            .1.8.1.1.32
--          acpmsTPFValueStr                         .1.8.1.1.33
--          acpmsTPFMinStr                           .1.8.1.1.34
--          acpmsTPFMaxStr                           .1.8.1.1.35
--          acpmsTPFAvgStr                           .1.8.1.1.36
--          acpmsTPFInEventState                     .1.8.1.1.37
--          acpmsPFPhaseAValueStr                    .1.8.1.1.38
--          acpmsPFPhaseBValueStr                    .1.8.1.1.39
--          acpmsPFPhaseCValueStr                    .1.8.1.1.40
--          acpmsTRcPValueStr                        .1.8.1.1.41
--          acpmsTRcPMinStr                          .1.8.1.1.42
--          acpmsTRcPMaxStr                          .1.8.1.1.43
--          acpmsTRcPAvgStr                          .1.8.1.1.44
--          acpmsRcPPhaseAValueStr                   .1.8.1.1.45
--          acpmsRcPPhaseBValueStr                   .1.8.1.1.46
--          acpmsRcPPhaseCValueStr                   .1.8.1.1.47
--          acpmsTAPValueStr                         .1.8.1.1.48
--          acpmsTAPMinStr                           .1.8.1.1.49
--          acpmsTAPMaxStr                           .1.8.1.1.50
--          acpmsTAPAvgStr                           .1.8.1.1.51
--          acpmsAPPhaseAValueStr                    .1.8.1.1.52
--          acpmsAPPhaseBValueStr                    .1.8.1.1.53
--          acpmsAPPhaseCValueStr                    .1.8.1.1.54
--          acpmsTotalEnergyWh                       .1.8.1.1.55
--          acpmsTotalEnergyVAR                      .1.8.1.1.56
--          acpmsTotalEnergyVA                       .1.8.1.1.57
--    batteryMonitorStatus                           .1.10
--      bmStatusTable                                .1.10.1
--        bmStatusEntry                              .1.10.1.1
--          bmsIndex                                 .1.10.1.1.1
--          bmsEnable                                .1.10.1.1.2
--          bmsName                                  .1.10.1.1.3
--          bmsState                                 .1.10.1.1.4
--          bmsStringState                           .1.10.1.1.5
--          bmsTempValue                             .1.10.1.1.6
--          bmsTempValueStr                          .1.10.1.1.7
--          bmsTempEvent                             .1.10.1.1.8
--          bmsDiffTempValue                         .1.10.1.1.9
--          bmsDiffTempValueStr                      .1.10.1.1.10
--          bmsDiffTempEvent                         .1.10.1.1.11
--          bmsVoltageValue                          .1.10.1.1.12
--          bmsVoltageEvent                          .1.10.1.1.13
--          bmsDiffVoltValue                         .1.10.1.1.14
--          bmsDiffVoltEvent                         .1.10.1.1.15
--          bmsCurrentValue                          .1.10.1.1.16
--          bmsChargingCurrentEvent                  .1.10.1.1.17
--          bmsDischargingCurrentEvent               .1.10.1.1.18
--          bmsChargeLevelValue                      .1.10.1.1.19
--          bmsChargeLevelEvent                      .1.10.1.1.20
--          bmsJarHealthValue                        .1.10.1.1.21
--          bmsJarHealthEvent                        .1.10.1.1.22
--          bmsCombined                              .1.10.1.1.23
--      bmJarStatusTable                             .1.10.2
--        bmJarStatusEntry                           .1.10.2.1
--          bmjsIndexBM                              .1.10.2.1.1
--          bmjsIndexJar                             .1.10.2.1.2
--          bmjsVoltageValue                         .1.10.2.1.3
--          bmjsTempValue                            .1.10.2.1.4
--          bmjsAdmittanceValue                      .1.10.2.1.5
--          bmjsAdmittanceChangeValue                .1.10.2.1.6
--  config                                           .2
--    eventSensorBasics                              .2.1
--      esNumberEventSensors                         .2.1.1
--      esTable                                      .2.1.2
--        esEntry                                    .2.1.2.1
--          esIndex                                  .2.1.2.1.1
--          esName                                   .2.1.2.1.2
--          esID                                     .2.1.2.1.3
--          esNumberTempSensors                      .2.1.2.1.4
--          esTempReportingMode                      .2.1.2.1.5
--          esNumberCCs                              .2.1.2.1.6
--          esCCReportingMode                        .2.1.2.1.7
--          esNumberHumidSensors                     .2.1.2.1.8
--          esHumidReportingMode                     .2.1.2.1.9
--          esNumberNoiseSensors                     .2.1.2.1.10
--          esNoiseReportingMode                     .2.1.2.1.11
--          esNumberAirflowSensors                   .2.1.2.1.12
--          esAirflowReportingMode                   .2.1.2.1.13
--          esNumberAnalog                           .2.1.2.1.14
--          esAnalogReportingMode                    .2.1.2.1.15
--          esNumberRelayOutputs                     .2.1.2.1.16
--          esRelayReportingMode                     .2.1.2.1.17
--          esTempCombinedStatus                     .2.1.2.1.18
--          esCCCombinedStatusBlock1                 .2.1.2.1.19
--          esCCCombinedStatusBlock2                 .2.1.2.1.20
--          esCCCombinedStatusBlock3                 .2.1.2.1.21
--          esCCCombinedStatusBlock4                 .2.1.2.1.22
--          esCCCombinedStatusBlock5                 .2.1.2.1.23
--          esCCCombinedStatusBlock6                 .2.1.2.1.24
--          esCCCombinedStatusBlock7                 .2.1.2.1.25
--          esCCCombinedStatusBlock8                 .2.1.2.1.26
--          esHumidCombinedStatus                    .2.1.2.1.27
--          esAnalogCombinedStatusBlock1             .2.1.2.1.28
--          esAnalogCombinedStatusBlock2             .2.1.2.1.29
--          esAnalogCombinedStatusBlock3             .2.1.2.1.30
--          esAnalogCombinedStatusBlock4             .2.1.2.1.31
--          esAnalogCombinedStatusBlock5             .2.1.2.1.32
--          esAnalogCombinedStatusBlock6             .2.1.2.1.33
--          esOutputCombinedStatusBlock1             .2.1.2.1.34
--          esOutputCombinedStatusBlock2             .2.1.2.1.35
--      esNewSensors                                 .2.1.3
--    eventSensorPointConfig                         .2.2
--      esPointConfigTempTable                       .2.2.1
--        esPointConfigTempEntry                     .2.2.1.1
--          espcTempIndexES                          .2.2.1.1.1
--          espcTempIndexPoint                       .2.2.1.1.2
--          espcTempEnable                           .2.2.1.1.3
--          espcTempScale                            .2.2.1.1.4
--          espcTempDeadband                         .2.2.1.1.5
--          espcTempVHighTemp                        .2.2.1.1.6
--          espcTempVHighActions                     .2.2.1.1.7
--          espcTempVHighTrapnum                     .2.2.1.1.8
--          espcTempVHighClass                       .2.2.1.1.9
--          espcTempHighTemp                         .2.2.1.1.10
--          espcTempHighActions                      .2.2.1.1.11
--          espcTempHighTrapnum                      .2.2.1.1.12
--          espcTempHighClass                        .2.2.1.1.13
--          espcTempNormalActions                    .2.2.1.1.14
--          espcTempNormalTrapnum                    .2.2.1.1.15
--          espcTempNormalClass                      .2.2.1.1.16
--          espcTempLowTemp                          .2.2.1.1.17
--          espcTempLowActions                       .2.2.1.1.18
--          espcTempLowTrapnum                       .2.2.1.1.19
--          espcTempLowClass                         .2.2.1.1.20
--          espcTempVLowTemp                         .2.2.1.1.21
--          espcTempVLowActions                      .2.2.1.1.22
--          espcTempVLowTrapnum                      .2.2.1.1.23
--          espcTempVLowClass                        .2.2.1.1.24
--      esPointConfigCCTable                         .2.2.2
--        esPointConfigCCEntry                       .2.2.2.1
--          espcCCIndexES                            .2.2.2.1.1
--          espcCCIndexPoint                         .2.2.2.1.2
--          espcCCEnable                             .2.2.2.1.3
--          espcCCName                               .2.2.2.1.4
--          espcCCEventState                         .2.2.2.1.5
--          espcCCThreshold                          .2.2.2.1.6
--          espcCCEventActions                       .2.2.2.1.7
--          espcCCEventTrapnum                       .2.2.2.1.8
--          espcCCEventClass                         .2.2.2.1.9
--          espcCCNormalActions                      .2.2.2.1.10
--          espcCCNormalTrapnum                      .2.2.2.1.11
--          espcCCNormalClass                        .2.2.2.1.12
--          espcCCAlarmAlias                         .2.2.2.1.13
--          espcCCNormalAlias                        .2.2.2.1.14
--          espcCCNormalThreshold                    .2.2.2.1.15
--      esPointConfigHumidTable                      .2.2.3
--        esPointConfigHumidEntry                    .2.2.3.1
--          espcHumidIndexES                         .2.2.3.1.1
--          espcHumidIndexPoint                      .2.2.3.1.2
--          espcHumidEnable                          .2.2.3.1.3
--          espcHumidDeadband                        .2.2.3.1.4
--          espcHumidVHighHumid                      .2.2.3.1.5
--          espcHumidVHighActions                    .2.2.3.1.6
--          espcHumidVHighTrapnum                    .2.2.3.1.7
--          espcHumidVHighClass                      .2.2.3.1.8
--          espcHumidHighHumid                       .2.2.3.1.9
--          espcHumidHighActions                     .2.2.3.1.10
--          espcHumidHighTrapnum                     .2.2.3.1.11
--          espcHumidHighClass                       .2.2.3.1.12
--          espcHumidNormalActions                   .2.2.3.1.13
--          espcHumidNormalTrapnum                   .2.2.3.1.14
--          espcHumidNormalClass                     .2.2.3.1.15
--          espcHumidLowHumid                        .2.2.3.1.16
--          espcHumidLowActions                      .2.2.3.1.17
--          espcHumidLowTrapnum                      .2.2.3.1.18
--          espcHumidLowClass                        .2.2.3.1.19
--          espcHumidVLowHumid                       .2.2.3.1.20
--          espcHumidVLowActions                     .2.2.3.1.21
--          espcHumidVLowTrapnum                     .2.2.3.1.22
--          espcHumidVLowClass                       .2.2.3.1.23
--      esPointConfigAITable                         .2.2.5
--        esPointConfigAIEntry                       .2.2.5.1
--          espcAIIndexES                            .2.2.5.1.1
--          espcAIIndexPoint                         .2.2.5.1.2
--          espcAIEnable                             .2.2.5.1.3
--          espcAIPolarity                           .2.2.5.1.4
--          espcAIDeadband                           .2.2.5.1.5
--          espcAIVhighValue                         .2.2.5.1.6
--          espcAIVhighActions                       .2.2.5.1.7
--          espcAIVhighTrapnum                       .2.2.5.1.8
--          espcAIVhighClass                         .2.2.5.1.9
--          espcAIHighValue                          .2.2.5.1.10
--          espcAIHighActions                        .2.2.5.1.11
--          espcAIHighTrapnum                        .2.2.5.1.12
--          espcAIHighClass                          .2.2.5.1.13
--          espcAINormalActions                      .2.2.5.1.14
--          espcAINormalTrapnum                      .2.2.5.1.15
--          espcAINormalClass                        .2.2.5.1.16
--          espcAILowValue                           .2.2.5.1.17
--          espcAILowActions                         .2.2.5.1.18
--          espcAILowTrapnum                         .2.2.5.1.19
--          espcAILowClass                           .2.2.5.1.20
--          espcAIVlowValue                          .2.2.5.1.21
--          espcAIVlowActions                        .2.2.5.1.22
--          espcAIVlowTrapnum                        .2.2.5.1.23
--          espcAIVlowClass                          .2.2.5.1.24
--          espcAIConvUnitName                       .2.2.5.1.25
--          espcAIConvHighValue                      .2.2.5.1.26
--          espcAIConvHighUnit                       .2.2.5.1.27
--          espcAIConvHighSign                       .2.2.5.1.28
--          espcAIConvLowValue                       .2.2.5.1.29
--          espcAIConvLowUnit                        .2.2.5.1.30
--          espcAIConvLowSign                        .2.2.5.1.31
--    serialPorts                                    .2.3
--      numberPorts                                  .2.3.1
--      portConfigTable                              .2.3.2
--        portConfigEntry                            .2.3.2.1
--          portConfigIndex                          .2.3.2.1.1
--          portConfigBaud                           .2.3.2.1.2
--          portConfigDataFormat                     .2.3.2.1.3
--          portConfigStripPtOutputLfs               .2.3.2.1.4
--          portConfigStripPtInputLfs                .2.3.2.1.5
--          portConfigMaskEnable                     .2.3.2.1.7
--          portConfigDAEnable                       .2.3.2.1.8
--          portConfigStoreAlarmsDPT                 .2.3.2.1.9
--          portConfigRecordTimeout                  .2.3.2.1.10
--          portConfigDataType                       .2.3.2.1.11
--          portConfigEtxToCRLF                      .2.3.2.1.12
--          portConfigMLREnable                      .2.3.2.1.13
--          portConfigMLRStartField1Pos              .2.3.2.1.14
--          portConfigMLRStartField1Text             .2.3.2.1.15
--          portConfigMLRStartField2Pos              .2.3.2.1.16
--          portConfigMLRStartField2Text             .2.3.2.1.17
--          portConfigMLRNumLinesBefore              .2.3.2.1.18
--          portConfigMLREndDetection                .2.3.2.1.19
--          portConfigMLRLineCount                   .2.3.2.1.20
--          portConfigMLREndField1Pos                .2.3.2.1.21
--          portConfigMLREndField1Text               .2.3.2.1.22
--          portConfigMLREndField2Pos                .2.3.2.1.23
--          portConfigMLREndField2Text               .2.3.2.1.24
--          portConfigMLRUseComplexRules             .2.3.2.1.25
--          portConfigBufferPT                       .2.3.2.1.26
--          portConfigId                             .2.3.2.1.27
--    network                                        .2.4
--      interface                                    .2.4.1
--        ethernet                                   .2.4.1.1
--          ethernet1                                .2.4.1.1.1
--            eth1Mode                               .2.4.1.1.1.1
--            eth1Address                            .2.4.1.1.1.2
--            eth1SubnetMask                         .2.4.1.1.1.3
--            eth1Router                             .2.4.1.1.1.4
--            eth1VLAN                               .2.4.1.1.1.5
--              eth1VLAN1                            .2.4.1.1.1.5.1
--                eth1VLAN1ID                        .2.4.1.1.1.5.1.1
--                eth1VLAN1Priority                  .2.4.1.1.1.5.1.2
--                eth1VLAN1Address                   .2.4.1.1.1.5.1.3
--                eth1VLAN1SubnetMask                .2.4.1.1.1.5.1.4
--                eth1VLAN1Router                    .2.4.1.1.1.5.1.5
--              eth1VLAN2                            .2.4.1.1.1.5.2
--                eth1VLAN2ID                        .2.4.1.1.1.5.2.1
--                eth1VLAN2Priority                  .2.4.1.1.1.5.2.2
--                eth1VLAN2Address                   .2.4.1.1.1.5.2.3
--                eth1VLAN2SubnetMask                .2.4.1.1.1.5.2.4
--                eth1VLAN2Router                    .2.4.1.1.1.5.2.5
--              eth1VLAN3                            .2.4.1.1.1.5.3
--                eth1VLAN3ID                        .2.4.1.1.1.5.3.1
--                eth1VLAN3Priority                  .2.4.1.1.1.5.3.2
--                eth1VLAN3Address                   .2.4.1.1.1.5.3.3
--                eth1VLAN3SubnetMask                .2.4.1.1.1.5.3.4
--                eth1VLAN3Router                    .2.4.1.1.1.5.3.5
--              eth1VLAN4                            .2.4.1.1.1.5.4
--                eth1VLAN4ID                        .2.4.1.1.1.5.4.1
--                eth1VLAN4Priority                  .2.4.1.1.1.5.4.2
--                eth1VLAN4Address                   .2.4.1.1.1.5.4.3
--                eth1VLAN4SubnetMask                .2.4.1.1.1.5.4.4
--                eth1VLAN4Router                    .2.4.1.1.1.5.4.5
--              eth1VLAN5                            .2.4.1.1.1.5.5
--                eth1VLAN5ID                        .2.4.1.1.1.5.5.1
--                eth1VLAN5Priority                  .2.4.1.1.1.5.5.2
--                eth1VLAN5Address                   .2.4.1.1.1.5.5.3
--                eth1VLAN5SubnetMask                .2.4.1.1.1.5.5.4
--                eth1VLAN5Router                    .2.4.1.1.1.5.5.5
--              eth1VLAN6                            .2.4.1.1.1.5.6
--                eth1VLAN6ID                        .2.4.1.1.1.5.6.1
--                eth1VLAN6Priority                  .2.4.1.1.1.5.6.2
--                eth1VLAN6Address                   .2.4.1.1.1.5.6.3
--                eth1VLAN6SubnetMask                .2.4.1.1.1.5.6.4
--                eth1VLAN6Router                    .2.4.1.1.1.5.6.5
--              eth1MAC                              .2.4.1.1.1.6
--          ethernet2                                .2.4.1.1.2
--            eth2Mode                               .2.4.1.1.2.1
--            eth2Address                            .2.4.1.1.2.2
--            eth2SubnetMask                         .2.4.1.1.2.3
--            eth2Router                             .2.4.1.1.2.4
--            eth2VLAN                               .2.4.1.1.2.5
--              eth2VLAN1                            .2.4.1.1.2.5.1
--                eth2VLAN1ID                        .2.4.1.1.2.5.1.1
--                eth2VLAN1Priority                  .2.4.1.1.2.5.1.2
--                eth2VLAN1Address                   .2.4.1.1.2.5.1.3
--                eth2VLAN1SubnetMask                .2.4.1.1.2.5.1.4
--                eth2VLAN1Router                    .2.4.1.1.2.5.1.5
--              eth2VLAN2                            .2.4.1.1.2.5.2
--                eth2VLAN2ID                        .2.4.1.1.2.5.2.1
--                eth2VLAN2Priority                  .2.4.1.1.2.5.2.2
--                eth2VLAN2Address                   .2.4.1.1.2.5.2.3
--                eth2VLAN2SubnetMask                .2.4.1.1.2.5.2.4
--                eth2VLAN2Router                    .2.4.1.1.2.5.2.5
--              eth2VLAN3                            .2.4.1.1.2.5.3
--                eth2VLAN3ID                        .2.4.1.1.2.5.3.1
--                eth2VLAN3Priority                  .2.4.1.1.2.5.3.2
--                eth2VLAN3Address                   .2.4.1.1.2.5.3.3
--                eth2VLAN3SubnetMask                .2.4.1.1.2.5.3.4
--                eth2VLAN3Router                    .2.4.1.1.2.5.3.5
--              eth2VLAN4                            .2.4.1.1.2.5.4
--                eth2VLAN4ID                        .2.4.1.1.2.5.4.1
--                eth2VLAN4Priority                  .2.4.1.1.2.5.4.2
--                eth2VLAN4Address                   .2.4.1.1.2.5.4.3
--                eth2VLAN4SubnetMask                .2.4.1.1.2.5.4.4
--                eth2VLAN4Router                    .2.4.1.1.2.5.4.5
--              eth2VLAN5                            .2.4.1.1.2.5.5
--                eth2VLAN5ID                        .2.4.1.1.2.5.5.1
--                eth2VLAN5Priority                  .2.4.1.1.2.5.5.2
--                eth2VLAN5Address                   .2.4.1.1.2.5.5.3
--                eth2VLAN5SubnetMask                .2.4.1.1.2.5.5.4
--                eth2VLAN5Router                    .2.4.1.1.2.5.5.5
--              eth2VLAN6                            .2.4.1.1.2.5.6
--                eth2VLAN6ID                        .2.4.1.1.2.5.6.1
--                eth2VLAN6Priority                  .2.4.1.1.2.5.6.2
--                eth2VLAN6Address                   .2.4.1.1.2.5.6.3
--                eth2VLAN6SubnetMask                .2.4.1.1.2.5.6.4
--                eth2VLAN6Router                    .2.4.1.1.2.5.6.5
--              eth2MAC                              .2.4.1.1.2.6
--      defaultRouter                                .2.4.2
--      dnsTable                                     .2.4.3
--        dnsEntry                                   .2.4.3.1
--          dnsIndex                                 .2.4.3.1.1
--          dnsAddress                               .2.4.3.1.2
--      hostname                                     .2.4.4
--      hostTable                                    .2.4.5
--        hostEntry                                  .2.4.5.1
--          hostIndex                                .2.4.5.1.1
--          hostDeclaration                          .2.4.5.1.2
--      ncpDuplex                                    .2.4.6
--      ncpTimeout                                   .2.4.7
--      snmp                                         .2.4.8
--        snmpAgentEnable                            .2.4.8.1
--        snmpNotificationTx                         .2.4.8.7
--          snmpNtfnAttempts                         .2.4.8.7.1
--          snmpNtfnTimeout                          .2.4.8.7.2
--          snmpNtfnCycles                           .2.4.8.7.3
--          snmpNtfnSnooze                           .2.4.8.7.4
--        snmpProxy                                  .2.4.8.8
--          snmpProxyTable                           .2.4.8.8.1
--            snmpProxyEntry                         .2.4.8.8.1.1
--              snmpProxyIndex                       .2.4.8.8.1.1.1
--              snmpProxyOIDBranch                   .2.4.8.8.1.1.2
--              snmpProxyIP                          .2.4.8.8.1.1.3
--              snmpProxyPort                        .2.4.8.8.1.1.4
--        snmpPoll                                   .2.4.8.9
--          snmpPMode                                .2.4.8.9.1
--          snmpPRequestTable                        .2.4.8.9.4
--            snmpPRequestEntry                      .2.4.8.9.4.1
--              snmpPRequestIndex                    .2.4.8.9.4.1.1
--              snmpPRequestDescription              .2.4.8.9.4.1.2
--              snmpPRequestAgent                    .2.4.8.9.4.1.3
--              snmpPRequestReadcom                  .2.4.8.9.4.1.4
--              snmpPRequestOID                      .2.4.8.9.4.1.5
--              snmpPRequestPeriod                   .2.4.8.9.4.1.6
--              snmpPRequestResultStatus             .2.4.8.9.4.1.10
--              snmpPRequestResultValue              .2.4.8.9.4.1.11
--              snmpPRequestResultTime               .2.4.8.9.4.1.12
--              snmpPRequestResultType               .2.4.8.9.4.1.13
--      ftpPush                                      .2.4.9
--        ftpPushEnable                              .2.4.9.1
--        ftpPushServer                              .2.4.9.2
--        ftpPushAccount                             .2.4.9.5
--        ftpPushDirectory                           .2.4.9.6
--        ftpPushperiod                              .2.4.9.7
--        ftpPushPushFileTable                       .2.4.9.8
--          ftpPushPushFileEntry                     .2.4.9.8.1
--            ftpPushPushFileIndex                   .2.4.9.8.1.1
--            ftpPushPushFile                        .2.4.9.8.1.2
--        ftpPushPushAudit                           .2.4.9.9
--        ftpPushPushAlarms                          .2.4.9.10
--        ftpPushRemoteFileTable                     .2.4.9.11
--          ftpPushRemoteFileEntry                   .2.4.9.11.1
--            ftpPushRemoteFileIndex                 .2.4.9.11.1.1
--            ftpPushRemoteFileName                  .2.4.9.11.1.2
--        ftpPushRemoteAlarmName                     .2.4.9.12
--        ftpPushPassive                             .2.4.9.13
--        ftpPushIncludeDate                         .2.4.9.14
--        ftpPushIncludeTime                         .2.4.9.15
--        ftpPushIncludeSeq                          .2.4.9.16
--      routing                                      .2.4.11
--        ethRoutingEnable                           .2.4.11.2
--        ethRoutingNATEnable                        .2.4.11.3
--      netSecurity                                  .2.4.12
--        ipRestriction                              .2.4.12.1
--          ipRestrictionTable                       .2.4.12.1.1
--            ipRestrictionEntry                     .2.4.12.1.1.1
--              ipRestrictionIndex                   .2.4.12.1.1.1.1
--              ipRestrictionEnable                  .2.4.12.1.1.1.2
--              ipRestrictionMask                    .2.4.12.1.1.1.3
--      rts                                          .2.4.13
--        rtsFileTable                               .2.4.13.1
--          rtsFileEntry                             .2.4.13.1.1
--            rtsFileIndex                           .2.4.13.1.1.1
--            rtsFileMode                            .2.4.13.1.1.2
--            rtsFileShowAnswer                      .2.4.13.1.1.3
--            rtsFileReqXON                          .2.4.13.1.1.4
--            rtsFileTimeout                         .2.4.13.1.1.5
--            rtsFileEmptyClose                      .2.4.13.1.1.6
--            rtsFilePushHost                        .2.4.13.1.1.7
--            rtsFilePushPort                        .2.4.13.1.1.8
--            rtsFilePushRetryTimer                  .2.4.13.1.1.9
--        rtsAlarms                                  .2.4.13.2
--          rtsAlarmsMode                            .2.4.13.2.1
--          rtsAlarmsShowAnswer                      .2.4.13.2.2
--          rtsAlarmsReqXON                          .2.4.13.2.3
--          rtsAlarmsTimeout                         .2.4.13.2.4
--          rtsAlarmsEmptyClose                      .2.4.13.2.5
--          rtsAlarmsPushHost                        .2.4.13.2.6
--          rtsAlarmsPushPort                        .2.4.13.2.7
--          rtsAlarmsPushRetryTimer                  .2.4.13.2.8
--      trap                                         .2.4.14
--        trapInclude                                .2.4.14.1
--          trapIncludeDateTime                      .2.4.14.1.1
--          trapIncludeSiteName                      .2.4.14.1.2
--          trapIncludeSensorID                      .2.4.14.1.3
--          trapIncludeUDName                        .2.4.14.1.4
--          trapIncludeUDState                       .2.4.14.1.5
--          trapIncludeSourceAddress                 .2.4.14.1.6
--        trapAuthFailEnable                         .2.4.14.2
--      wireless                                     .2.4.16
--        wirelessMode                               .2.4.16.1
--        wirelessAPN                                .2.4.16.2
--        wirelessIdleTimeout                        .2.4.16.3
--        wirelessPIN                                .2.4.16.5
--        wirelessDRE                                .2.4.16.9
--      email                                        .2.4.17
--        emailServer                                .2.4.17.1
--        emailDomain                                .2.4.17.2
--        emailAuthEnable                            .2.4.17.3
--      netAdvanced                                  .2.4.18
--        arpFilter                                  .2.4.18.1
--      web                                          .2.4.19
--        webEnable                                  .2.4.19.1
--        webPort                                    .2.4.19.1
--        webTimeout                                 .2.4.19.1
--    time                                           .2.8
--      clock                                        .2.8.1
--    console                                        .2.10
--      consoleDuplex                                .2.10.1
--      consoleTimeout                               .2.10.2
--      consoleConfirm                               .2.10.7
--    unitSecurity                                   .2.11
--      secCore                                      .2.11.1
--        scShowPasswordPrompt                       .2.11.1.1
--        scConsoleLoginRequired                     .2.11.1.2
--        scModemLoginRequired                       .2.11.1.3
--        scTelnetLoginRequired                      .2.11.1.4
--        scTelnetPTLoginRequired                    .2.11.1.5
--        scRTSLoginRequired                         .2.11.1.6
--        scAuthMode                                 .2.11.1.7
--        scRightsGroup                              .2.11.1.8
--        scSecret                                   .2.11.1.9
--      secUserTable                                 .2.11.2
--        secUserEntry                               .2.11.2.1
--          secUserIndex                             .2.11.2.1.1
--          secUserEnable                            .2.11.2.1.2
--          secUserConnectVia                        .2.11.2.1.5
--          secUserLoginTo                           .2.11.2.1.6
--          secUserAccessFile                        .2.11.2.1.7
--          secUserPTEscapeTo                        .2.11.2.1.9
--          secUserPPPType                           .2.11.2.1.10
--          secUserRights                            .2.11.2.1.11
--          secUserEventsReadAccess                  .2.11.2.1.13
--          secUserAuditReadAccess                   .2.11.2.1.14
--          secUserEventsWriteAccess                 .2.11.2.1.16
--          secUserAuditWriteAccess                  .2.11.2.1.17
--          secUserExpiration                        .2.11.2.1.18
--          secUserCallbackNumber1                   .2.11.2.1.19
--          secUserCallbackNumber2                   .2.11.2.1.20
--          secUserCallbackNumber3                   .2.11.2.1.21
--          secUserChallengeTelnetMode               .2.11.2.1.22
--          secUserChallengeModemMode                .2.11.2.1.23
--          secUserChallengeConsoleMode              .2.11.2.1.24
--          secUserChallengeTelnetSendTo             .2.11.2.1.25
--          secUserChallengeModemSendTo              .2.11.2.1.26
--          secUserChallengeExpiration               .2.11.2.1.27
--      secFactory                                   .2.11.3
--        sfEnable                                   .2.11.3.1
--        sfSecret                                   .2.11.3.2
--    event                                          .2.12
--      evCore                                       .2.12.1
--        evClassNameTable                           .2.12.1.1
--          evClassNameEntry                         .2.12.1.1.1
--            evClassNameIndex                       .2.12.1.1.1.1
--            evClassName                            .2.12.1.1.1.2
--        evReminderInterval                         .2.12.1.2
--        evLog                                      .2.12.1.3
--          evLogEnable                              .2.12.1.3.1
--          evLogStoreAlarm                          .2.12.1.3.2
--          evLogMaxSize                             .2.12.1.3.3
--          evLogStoreSensor                         .2.12.1.3.4
--          evLogTimeStampAlarms                     .2.12.1.3.5
--          evLogPrependName                         .2.12.1.3.6
--        evMgmt                                     .2.12.1.4
--          evMgmtReprocess                          .2.12.1.4.3
--      evSched1                                     .2.12.5
--        evSched1Enable                             .2.12.5.1
--        evSched1Actions                            .2.12.5.2
--        evSched1Message                            .2.12.5.3
--        evSched1TrapNum                            .2.12.5.4
--        evSched1Class                              .2.12.5.5
--        evSched1Sunday                             .2.12.5.6
--        evSched1Monday                             .2.12.5.7
--        evSched1Tuesday                            .2.12.5.8
--        evSched1Wednesday                          .2.12.5.9
--        evSched1Thursday                           .2.12.5.10
--        evSched1Friday                             .2.12.5.11
--        evSched1Saturday                           .2.12.5.12
--        evSched1Exclusions                         .2.12.5.13
--      evSched2                                     .2.12.6
--        evSched2Enable                             .2.12.6.1
--        evSched2Actions                            .2.12.6.2
--        evSched2Message                            .2.12.6.3
--        evSched2TrapNum                            .2.12.6.4
--        evSched2Class                              .2.12.6.5
--        evSched2Sunday                             .2.12.6.6
--        evSched2Monday                             .2.12.6.7
--        evSched2Tuesday                            .2.12.6.8
--        evSched2Wednesday                          .2.12.6.9
--        evSched2Thursday                           .2.12.6.10
--        evSched2Friday                             .2.12.6.11
--        evSched2Saturday                           .2.12.6.12
--        evSched2Exclusions                         .2.12.6.13
--      evShskLowTable                               .2.12.7
--        evShskLowEntry                             .2.12.7.1
--          evShskLowIndex                           .2.12.7.1.1
--          evShskLowEnable                          .2.12.7.1.2
--          evShskLowActions                         .2.12.7.1.3
--          evShskLowMessage                         .2.12.7.1.4
--          evShskLowClass                           .2.12.7.1.5
--          evShskLowTrapNum                         .2.12.7.1.6
--      evShskHighTable                              .2.12.8
--        evShskHighEntry                            .2.12.8.1
--          evShskHighIndex                          .2.12.8.1.1
--          evShskHighEnable                         .2.12.8.1.2
--          evShskHighActions                        .2.12.8.1.3
--          evShskHighMessage                        .2.12.8.1.4
--          evShskHighClass                          .2.12.8.1.5
--          evShskHighTrapNum                        .2.12.8.1.6
--      evNoSensor                                   .2.12.9
--        evNoSensorTimeout                          .2.12.9.1
--        evNoSensorActions                          .2.12.9.2
--        evNoSensorTrapNum                          .2.12.9.3
--        evNoSensorClass                            .2.12.9.4
--      fuelSensor                                   .2.12.11
--        fuelSensorGeneralTable                     .2.12.11.1
--          fsGenEntry                               .2.12.11.1.1
--            fsGenIndex                             .2.12.11.1.1.1
--            fsGenName                              .2.12.11.1.1.2
--            fsGenSensorType                        .2.12.11.1.1.3
--            fsGenDistanceUnit                      .2.12.11.1.1.4
--            fsGenRawValueTop                       .2.12.11.1.1.5
--            fsGenTopOffset                         .2.12.11.1.1.6
--            fsGenRawValueBottom                    .2.12.11.1.1.7
--            fsGenBottomOffset                      .2.12.11.1.1.8
--            fsGenInputES                           .2.12.11.1.1.9
--            fsGenInputPoint                        .2.12.11.1.1.10
--            fsGenFilterAveraging                   .2.12.11.1.1.11
--            fsGenSysrepEnable                      .2.12.11.1.1.12
--            fsGenSysrepThreshold                   .2.12.11.1.1.13
--            fsGenSysrepLimit                       .2.12.11.1.1.14
--            fsGenSysrepPackage                     .2.12.11.1.1.15
--            fsGenSysrepType                        .2.12.11.1.1.16
--        fuelSensorTankTable                        .2.12.11.2
--          fsTankEntry                              .2.12.11.2.1
--            fsTankIndex                            .2.12.11.2.1.1
--            fsTankHeight                           .2.12.11.2.1.2
--            fsTankDimA                             .2.12.11.2.1.3
--            fsTankDimB                             .2.12.11.2.1.4
--            fsTankVolume                           .2.12.11.2.1.5
--            fsTankVolumeUnit                       .2.12.11.2.1.6
--            fsTankShape                            .2.12.11.2.1.7
--        fuelSensorCustomTankTable                  .2.12.11.3
--          fsCustomTankEntry                        .2.12.11.3.1
--            fsCustomTankIndexFS                    .2.12.11.3.1.1
--            fsCustomTankIndexDatum                 .2.12.11.3.1.2
--            fsCustomTankHeight                     .2.12.11.3.1.3
--            fsCustomTankVolume                     .2.12.11.3.1.4
--        fuelSensorVolumeTable                      .2.12.11.4
--          fsVolumeEntry                            .2.12.11.4.1
--            fsVolumeIndex                          .2.12.11.4.1.1
--            fsVolumeEnable                         .2.12.11.4.1.2
--            fsVolumeDeadband                       .2.12.11.4.1.3
--            fsVolumeVHighValue                     .2.12.11.4.1.4
--            fsVolumeVHighActions                   .2.12.11.4.1.5
--            fsVolumeVHighTrapNum                   .2.12.11.4.1.6
--            fsVolumeVHighClass                     .2.12.11.4.1.7
--            fsVolumeHighValue                      .2.12.11.4.1.8
--            fsVolumeHighActions                    .2.12.11.4.1.9
--            fsVolumeHighTrapNum                    .2.12.11.4.1.10
--            fsVolumeHighClass                      .2.12.11.4.1.11
--            fsVolumeNormalActions                  .2.12.11.4.1.12
--            fsVolumeNormalTrapNum                  .2.12.11.4.1.13
--            fsVolumeNormalClass                    .2.12.11.4.1.14
--            fsVolumeLowValue                       .2.12.11.4.1.15
--            fsVolumeLowActions                     .2.12.11.4.1.16
--            fsVolumeLowTrapNum                     .2.12.11.4.1.17
--            fsVolumeLowClass                       .2.12.11.4.1.18
--            fsVolumeVLowValue                      .2.12.11.4.1.19
--            fsVolumeVLowActions                    .2.12.11.4.1.20
--            fsVolumeVLowTrapNum                    .2.12.11.4.1.21
--            fsVolumeVLowClass                      .2.12.11.4.1.22
--        fuelSensorDisconnectTable                  .2.12.11.5
--          fsDiscEntry                              .2.12.11.5.1
--            fsDiscIndex                            .2.12.11.5.1.1
--            fsDiscEnable                           .2.12.11.5.1.2
--            fsDiscHighValue                        .2.12.11.5.1.3
--            fsDiscLowValue                         .2.12.11.5.1.4
--            fsDiscActions                          .2.12.11.5.1.5
--            fsDiscTrapNum                          .2.12.11.5.1.6
--            fsDiscClass                            .2.12.11.5.1.7
--            fsDiscNormalActions                    .2.12.11.5.1.8
--            fsDiscNormalTrapNum                    .2.12.11.5.1.9
--            fsDiscNormalClass                      .2.12.11.5.1.10
--        fuelSensorSuddenChangeTable                .2.12.11.6
--          fsSuddenChangeEntry                      .2.12.11.6.1
--            fsSuddenChangeIndex                    .2.12.11.6.1.1
--            fsSuddenChangeEnable                   .2.12.11.6.1.2
--            fsSuddenChangeTime                     .2.12.11.6.1.3
--            fsSuddenChangeAmplitude                .2.12.11.6.1.4
--            fsSuddenChangeActions                  .2.12.11.6.1.5
--            fsSuddenChangeTrapNum                  .2.12.11.6.1.6
--            fsSuddenChangeClass                    .2.12.11.6.1.7
--        fuelSensorSlowChangeTable                  .2.12.11.7
--          fuelSensorSlowChangeEntry                .2.12.11.7.1
--            fsSlowChangeIndex                      .2.12.11.7.1.1
--            fsSlowChangeEnable                     .2.12.11.7.1.2
--            fsSlowChangeTime                       .2.12.11.7.1.3
--            fsSlowChangeAmplitude                  .2.12.11.7.1.4
--            fsSlowChangeActions                    .2.12.11.7.1.5
--            fsSlowChangeTrapNum                    .2.12.11.7.1.6
--            fsSlowChangeClass                      .2.12.11.7.1.7
--      acPowerMonitor                               .2.12.12
--        acpmGeneralTable                           .2.12.12.1
--          acpmGenEntry                             .2.12.12.1.1
--            acpmGenIndex                           .2.12.12.1.1.1
--            acpmGenDevice                          .2.12.12.1.1.2
--            acpmGenName                            .2.12.12.1.1.3
--            acpmGenAddress                         .2.12.12.1.1.4
--            acpmGenPtRatio                         .2.12.12.1.1.5
--            acpmGenCtRatio                         .2.12.12.1.1.6
--            acpmGenPowerType                       .2.12.12.1.1.7
--            acpmGenSysrepPackage                   .2.12.12.1.1.8
--            acpmGenSysrepType                      .2.12.12.1.1.9
--        acpmAvgVoltageTable                        .2.12.12.2
--          acpmAvgVoltageEntry                      .2.12.12.2.1
--            acpmAvgVoltageIndex                    .2.12.12.2.1.1
--            acpmAvgVoltageEnable                   .2.12.12.2.1.2
--            acpmAvgVoltageDeadband                 .2.12.12.2.1.3
--            acpmAvgVoltageVHighValue               .2.12.12.2.1.4
--            acpmAvgVoltageVHighActions             .2.12.12.2.1.5
--            acpmAvgVoltageVHighTrapNum             .2.12.12.2.1.6
--            acpmAvgVoltageVHighClass               .2.12.12.2.1.7
--            acpmAvgVoltageHighValue                .2.12.12.2.1.8
--            acpmAvgVoltageHighActions              .2.12.12.2.1.9
--            acpmAvgVoltageHighTrapNum              .2.12.12.2.1.10
--            acpmAvgVoltageHighClass                .2.12.12.2.1.11
--            acpmAvgVoltageNormalActions            .2.12.12.2.1.12
--            acpmAvgVoltageNormalTrapNum            .2.12.12.2.1.13
--            acpmAvgVoltageNormalClass              .2.12.12.2.1.14
--            acpmAvgVoltageLowValue                 .2.12.12.2.1.15
--            acpmAvgVoltageLowActions               .2.12.12.2.1.16
--            acpmAvgVoltageLowTrapNum               .2.12.12.2.1.17
--            acpmAvgVoltageLowClass                 .2.12.12.2.1.18
--            acpmAvgVoltageVLowValue                .2.12.12.2.1.19
--            acpmAvgVoltageVLowActions              .2.12.12.2.1.20
--            acpmAvgVoltageVLowTrapNum              .2.12.12.2.1.21
--            acpmAvgVoltageVLowClass                .2.12.12.2.1.22
--            acpmAvgVoltageSysrepEnable             .2.12.12.2.1.23
--            acpmAvgVoltageSysrepThreshold          .2.12.12.2.1.24
--            acpmAvgVoltageSysrepLimit              .2.12.12.2.1.25
--        acpmAvgCurrentTable                        .2.12.12.3
--          acpmAvgCurrentEntry                      .2.12.12.3.1
--            acpmAvgCurrentIndex                    .2.12.12.3.1.1
--            acpmAvgCurrentEnable                   .2.12.12.3.1.2
--            acpmAvgCurrentDeadband                 .2.12.12.3.1.3
--            acpmAvgCurrentVHighValue               .2.12.12.3.1.4
--            acpmAvgCurrentVHighActions             .2.12.12.3.1.5
--            acpmAvgCurrentVHighTrapNum             .2.12.12.3.1.6
--            acpmAvgCurrentVHighClass               .2.12.12.3.1.7
--            acpmAvgCurrentHighValue                .2.12.12.3.1.8
--            acpmAvgCurrentHighActions              .2.12.12.3.1.9
--            acpmAvgCurrentHighTrapNum              .2.12.12.3.1.10
--            acpmAvgCurrentHighClass                .2.12.12.3.1.11
--            acpmAvgCurrentNormalActions            .2.12.12.3.1.12
--            acpmAvgCurrentNormalTrapNum            .2.12.12.3.1.13
--            acpmAvgCurrentNormalClass              .2.12.12.3.1.14
--            acpmAvgCurrentLowValue                 .2.12.12.3.1.15
--            acpmAvgCurrentLowActions               .2.12.12.3.1.16
--            acpmAvgCurrentLowTrapNum               .2.12.12.3.1.17
--            acpmAvgCurrentLowClass                 .2.12.12.3.1.18
--            acpmAvgCurrentVLowValue                .2.12.12.3.1.19
--            acpmAvgCurrentVLowActions              .2.12.12.3.1.20
--            acpmAvgCurrentVLowTrapNum              .2.12.12.3.1.21
--            acpmAvgCurrentVLowClass                .2.12.12.3.1.22
--            acpmAvgCurrentSysrepEnable             .2.12.12.3.1.23
--            acpmAvgCurrentSysrepThreshold          .2.12.12.3.1.24
--            acpmAvgCurrentSysrepLimit              .2.12.12.3.1.25
--        acpmFreqTable                              .2.12.12.4
--          acpmFreqEntry                            .2.12.12.4.1
--            acpmFreqIndex                          .2.12.12.4.1.1
--            acpmFreqEnable                         .2.12.12.4.1.2
--            acpmFreqDeadband                       .2.12.12.4.1.3
--            acpmFreqVHighValue                     .2.12.12.4.1.4
--            acpmFreqVHighActions                   .2.12.12.4.1.5
--            acpmFreqVHighTrapNum                   .2.12.12.4.1.6
--            acpmFreqVHighClass                     .2.12.12.4.1.7
--            acpmFreqHighValue                      .2.12.12.4.1.8
--            acpmFreqHighActions                    .2.12.12.4.1.9
--            acpmFreqHighTrapNum                    .2.12.12.4.1.10
--            acpmFreqHighClass                      .2.12.12.4.1.11
--            acpmFreqNormalActions                  .2.12.12.4.1.12
--            acpmFreqNormalTrapNum                  .2.12.12.4.1.13
--            acpmFreqNormalClass                    .2.12.12.4.1.14
--            acpmFreqLowValue                       .2.12.12.4.1.15
--            acpmFreqLowActions                     .2.12.12.4.1.16
--            acpmFreqLowTrapNum                     .2.12.12.4.1.17
--            acpmFreqLowClass                       .2.12.12.4.1.18
--            acpmFreqVLowValue                      .2.12.12.4.1.19
--            acpmFreqVLowActions                    .2.12.12.4.1.20
--            acpmFreqVLowTrapNum                    .2.12.12.4.1.21
--            acpmFreqVLowClass                      .2.12.12.4.1.22
--            acpmFreqSysrepEnable                   .2.12.12.4.1.23
--            acpmFreqSysrepThreshold                .2.12.12.4.1.24
--            acpmFreqSysrepLimit                    .2.12.12.4.1.25
--        acpmTotalRealPowerTable                    .2.12.12.5
--          acpmTRPEntry                             .2.12.12.5.1
--            acpmTRPIndex                           .2.12.12.5.1.1
--            acpmTRPEnable                          .2.12.12.5.1.2
--            acpmTRPDeadband                        .2.12.12.5.1.3
--            acpmTRPVHighValue                      .2.12.12.5.1.4
--            acpmTRPVHighActions                    .2.12.12.5.1.5
--            acpmTRPVHighTrapNum                    .2.12.12.5.1.6
--            acpmTRPVHighClass                      .2.12.12.5.1.7
--            acpmTRPHighValue                       .2.12.12.5.1.8
--            acpmTRPHighActions                     .2.12.12.5.1.9
--            acpmTRPHighTrapNum                     .2.12.12.5.1.10
--            acpmTRPHighClass                       .2.12.12.5.1.11
--            acpmTRPNormalActions                   .2.12.12.5.1.12
--            acpmTRPNormalTrapNum                   .2.12.12.5.1.13
--            acpmTRPNormalClass                     .2.12.12.5.1.14
--            acpmTRPLowValue                        .2.12.12.5.1.15
--            acpmTRPLowActions                      .2.12.12.5.1.16
--            acpmTRPLowTrapNum                      .2.12.12.5.1.17
--            acpmTRPLowClass                        .2.12.12.5.1.18
--            acpmTRPVLowValue                       .2.12.12.5.1.19
--            acpmTRPVLowActions                     .2.12.12.5.1.20
--            acpmTRPVLowTrapNum                     .2.12.12.5.1.21
--            acpmTRPVLowClass                       .2.12.12.5.1.22
--            acpmTRPSysrepEnable                    .2.12.12.5.1.23
--            acpmTRPSysrepThreshold                 .2.12.12.5.1.24
--            acpmTRPSysrepLimit                     .2.12.12.5.1.25
--        acpmDisconnectTable                        .2.12.12.6
--          acpmDisconnectEntry                      .2.12.12.6.1
--            acpmDisconnectIndex                    .2.12.12.6.1.1
--            acpmDisconnectEnable                   .2.12.12.6.1.2
--            acpmDisconnectActions                  .2.12.12.6.1.3
--            acpmDisconnectTrapNum                  .2.12.12.6.1.4
--            acpmDisconnectClass                    .2.12.12.6.1.5
--            acpmDisconnectNormalActions            .2.12.12.6.1.6
--            acpmDisconnectNormalTrapNum            .2.12.12.6.1.7
--            acpmDisconnectNormalClass              .2.12.12.6.1.8
--      batteryMonitor                               .2.12.14
--        batteryMonitorGeneralTable                 .2.12.14.1
--          bmGenEntry                               .2.12.14.1.1
--            bmGenIndex                             .2.12.14.1.1.1
--            bmGenEnable                            .2.12.14.1.1.2
--            bmGenName                              .2.12.14.1.1.3
--            bmGenBatteryQuantity                   .2.12.14.1.1.4
--            bmGenBatteryCapacity                   .2.12.14.1.1.5
--            bmGenBatteryNominalVoltage             .2.12.14.1.1.6
--            bmGenSysrepPackage                     .2.12.14.1.1.7
--            bmGenSysrepType                        .2.12.14.1.1.8
--        batteryMonitorDeviceTable                  .2.12.14.2
--          bmDeviceEntry                            .2.12.14.2.1
--            bmDeviceIndex                          .2.12.14.2.1.1
--            bmDeviceType                           .2.12.14.2.1.2
--            bmDeviceES                             .2.12.14.2.1.3
--            bmDeviceIP                             .2.12.14.2.1.4
--            bmDeviceReadcom                        .2.12.14.2.1.5
--            bmDeviceInputString                    .2.12.14.2.1.6
--            bmDeviceCTSize                         .2.12.14.2.1.7
--        batteryMonitorTempTable                    .2.12.14.3
--          bmTempEntry                              .2.12.14.3.1
--            bmTempIndex                            .2.12.14.3.1.1
--            bmTempEnable                           .2.12.14.3.1.2
--            bmTempDeadband                         .2.12.14.3.1.3
--            bmTempScale                            .2.12.14.3.1.4
--            bmTempHighValue                        .2.12.14.3.1.5
--            bmTempHighActions                      .2.12.14.3.1.6
--            bmTempHighTrapNum                      .2.12.14.3.1.7
--            bmTempHighClass                        .2.12.14.3.1.8
--            bmTempNormalActions                    .2.12.14.3.1.9
--            bmTempNormalTrapNum                    .2.12.14.3.1.10
--            bmTempNormalClass                      .2.12.14.3.1.11
--            bmTempLowValue                         .2.12.14.3.1.12
--            bmTempLowActions                       .2.12.14.3.1.13
--            bmTempLowTrapNum                       .2.12.14.3.1.14
--            bmTempLowClass                         .2.12.14.3.1.15
--            bmTempSysrepEnable                     .2.12.14.3.1.16
--            bmTempSysrepThreshold                  .2.12.14.3.1.17
--            bmTempSysrepLimit                      .2.12.14.3.1.18
--        batteryMonitorDiffTempTable                .2.12.14.4
--          bmDiffTempEntry                          .2.12.14.4.1
--            bmDiffTempIndex                        .2.12.14.4.1.1
--            bmDiffTempEnable                       .2.12.14.4.1.2
--            bmDiffTempDeadband                     .2.12.14.4.1.3
--            bmDiffTempVHighValue                   .2.12.14.4.1.4
--            bmDiffTempVHighActions                 .2.12.14.4.1.5
--            bmDiffTempVHighTrapNum                 .2.12.14.4.1.6
--            bmDiffTempVHighClass                   .2.12.14.4.1.7
--            bmDiffTempHighValue                    .2.12.14.4.1.8
--            bmDiffTempHighActions                  .2.12.14.4.1.9
--            bmDiffTempHighTrapNum                  .2.12.14.4.1.10
--            bmDiffTempHighClass                    .2.12.14.4.1.11
--            bmDiffTempNormalActions                .2.12.14.4.1.12
--            bmDiffTempNormalTrapNum                .2.12.14.4.1.13
--            bmDiffTempNormalClass                  .2.12.14.4.1.14
--            bmDiffTempSysrepEnable                 .2.12.14.4.1.15
--            bmDiffTempSysrepThreshold              .2.12.14.4.1.16
--            bmDiffTempSysrepLimit                  .2.12.14.4.1.17
--        batteryMonitorVoltageTable                 .2.12.14.5
--          bmVoltageEntry                           .2.12.14.5.1
--            bmVoltageIndex                         .2.12.14.5.1.1
--            bmVoltageEnable                        .2.12.14.5.1.2
--            bmVoltageDeadband                      .2.12.14.5.1.3
--            bmVoltageVHighValue                    .2.12.14.5.1.4
--            bmVoltageVHighActions                  .2.12.14.5.1.5
--            bmVoltageVHighTrapNum                  .2.12.14.5.1.6
--            bmVoltageVHighClass                    .2.12.14.5.1.7
--            bmVoltageHighValue                     .2.12.14.5.1.8
--            bmVoltageHighActions                   .2.12.14.5.1.9
--            bmVoltageHighTrapNum                   .2.12.14.5.1.10
--            bmVoltageHighClass                     .2.12.14.5.1.11
--            bmVoltageNormalActions                 .2.12.14.5.1.12
--            bmVoltageNormalTrapNum                 .2.12.14.5.1.13
--            bmVoltageNormalClass                   .2.12.14.5.1.14
--            bmVoltageLowValue                      .2.12.14.5.1.15
--            bmVoltageLowActions                    .2.12.14.5.1.16
--            bmVoltageLowTrapNum                    .2.12.14.5.1.17
--            bmVoltageLowClass                      .2.12.14.5.1.18
--            bmVoltageVLowValue                     .2.12.14.5.1.19
--            bmVoltageVLowActions                   .2.12.14.5.1.20
--            bmVoltageVLowTrapNum                   .2.12.14.5.1.21
--            bmVoltageVLowClass                     .2.12.14.5.1.22
--            bmVoltageSysrepEnable                  .2.12.14.5.1.23
--            bmVoltageSysrepThreshold               .2.12.14.5.1.24
--            bmVoltageSysrepLimit                   .2.12.14.5.1.25
--        batteryMonitorDiffVoltTable                .2.12.14.6
--          bmDiffVoltEntry                          .2.12.14.6.1
--            bmDiffVoltIndex                        .2.12.14.6.1.1
--            bmDiffVoltEnable                       .2.12.14.6.1.2
--            bmDiffVoltDeadband                     .2.12.14.6.1.3
--            bmDiffVoltVHighValue                   .2.12.14.6.1.4
--            bmDiffVoltVHighActions                 .2.12.14.6.1.5
--            bmDiffVoltVHighTrapNum                 .2.12.14.6.1.6
--            bmDiffVoltVHighClass                   .2.12.14.6.1.7
--            bmDiffVoltHighValue                    .2.12.14.6.1.8
--            bmDiffVoltHighActions                  .2.12.14.6.1.9
--            bmDiffVoltHighTrapNum                  .2.12.14.6.1.10
--            bmDiffVoltHighClass                    .2.12.14.6.1.11
--            bmDiffVoltNormalActions                .2.12.14.6.1.12
--            bmDiffVoltNormalTrapNum                .2.12.14.6.1.13
--            bmDiffVoltNormalClass                  .2.12.14.6.1.14
--            bmDiffVoltSysrepEnable                 .2.12.14.6.1.15
--            bmDiffVoltSysrepThreshold              .2.12.14.6.1.16
--            bmDiffVoltSysrepLimit                  .2.12.14.6.1.17
--        batteryMonitorChargingCurrentTable         .2.12.14.7
--          bmChargingCurrentEntry                   .2.12.14.7.1
--            bmChargingCurrentIndex                 .2.12.14.7.1.1
--            bmChargingCurrentEnable                .2.12.14.7.1.2
--            bmChargingCurrentDeadband              .2.12.14.7.1.3
--            bmChargingCurrentVHighValue            .2.12.14.7.1.4
--            bmChargingCurrentVHighActions          .2.12.14.7.1.5
--            bmChargingCurrentVHighTrapNum          .2.12.14.7.1.6
--            bmChargingCurrentVHighClass            .2.12.14.7.1.7
--            bmChargingCurrentHighValue             .2.12.14.7.1.8
--            bmChargingCurrentHighActions           .2.12.14.7.1.9
--            bmChargingCurrentHighTrapNum           .2.12.14.7.1.10
--            bmChargingCurrentHighClass             .2.12.14.7.1.11
--            bmChargingCurrentNormalActions         .2.12.14.7.1.12
--            bmChargingCurrentNormalTrapNum         .2.12.14.7.1.13
--            bmChargingCurrentNormalClass           .2.12.14.7.1.14
--            bmChargingCurrentSysrepEnable          .2.12.14.7.1.15
--            bmChargingCurrentSysrepThreshold       .2.12.14.7.1.16
--            bmChargingCurrentSysrepLimit           .2.12.14.7.1.17
--        batteryMonitorDischargingCurrentTable      .2.12.14.8
--          bmDischargingCurrentEntry                .2.12.14.8.1
--            bmDischargingCurrentIndex              .2.12.14.8.1.1
--            bmDischargingCurrentEnable             .2.12.14.8.1.2
--            bmDischargingCurrentDeadband           .2.12.14.8.1.3
--            bmDischargingCurrentVHighValue         .2.12.14.8.1.4
--            bmDischargingCurrentVHighActions       .2.12.14.8.1.5
--            bmDischargingCurrentVHighTrapNum       .2.12.14.8.1.6
--            bmDischargingCurrentVHighClass         .2.12.14.8.1.7
--            bmDischargingCurrentHighValue          .2.12.14.8.1.8
--            bmDischargingCurrentHighActions        .2.12.14.8.1.9
--            bmDischargingCurrentHighTrapNum        .2.12.14.8.1.10
--            bmDischargingCurrentHighClass          .2.12.14.8.1.11
--            bmDischargingCurrentNormalActions      .2.12.14.8.1.12
--            bmDischargingCurrentNormalTrapNum      .2.12.14.8.1.13
--            bmDischargingCurrentNormalClass        .2.12.14.8.1.14
--            bmDischargingCurrentSysrepEnable       .2.12.14.8.1.15
--            bmDischargingCurrentSysrepThreshold    .2.12.14.8.1.16
--            bmDischargingCurrentSysrepLimit        .2.12.14.8.1.17
--        batteryMonitorChargeLevelTable             .2.12.14.9
--          bmChargeLevelEntry                       .2.12.14.9.1
--            bmChargeLevelIndex                     .2.12.14.9.1.1
--            bmChargeLevelEnable                    .2.12.14.9.1.2
--            bmChargeLevelNormalActions             .2.12.14.9.1.3
--            bmChargeLevelNormalTrapNum             .2.12.14.9.1.4
--            bmChargeLevelNormalClass               .2.12.14.9.1.5
--            bmChargeLevelLowActions                .2.12.14.9.1.6
--            bmChargeLevelLowTrapNum                .2.12.14.9.1.7
--            bmChargeLevelLowClass                  .2.12.14.9.1.8
--            bmChargeLevelVLowActions               .2.12.14.9.1.9
--            bmChargeLevelVLowTrapNum               .2.12.14.9.1.10
--            bmChargeLevelVLowClass                 .2.12.14.9.1.11
--            bmChargeLevelSysrepEnable              .2.12.14.9.1.12
--        batteryMonitorJarHealthTable               .2.12.14.10
--          bmJarHealthEntry                         .2.12.14.10.1
--            bmJarHealthIndex                       .2.12.14.10.1.1
--            bmJarHealthEnable                      .2.12.14.10.1.2
--            bmJarHealthNormalActions               .2.12.14.10.1.3
--            bmJarHealthNormalTrapNum               .2.12.14.10.1.4
--            bmJarHealthNormalClass                 .2.12.14.10.1.5
--            bmJarHealthLowActions                  .2.12.14.10.1.6
--            bmJarHealthLowTrapNum                  .2.12.14.10.1.7
--            bmJarHealthLowClass                    .2.12.14.10.1.8
--            bmJarHealthVLowActions                 .2.12.14.10.1.9
--            bmJarHealthVLowTrapNum                 .2.12.14.10.1.10
--            bmJarHealthVLowClass                   .2.12.14.10.1.11
--            bmJarHealthSysrepEnable                .2.12.14.10.1.12
--      evReset                                      .2.12.16
--        evResetEnable                              .2.12.16.1
--        evResetDelay                               .2.12.16.2
--        evResetActions                             .2.12.16.3
--        evResetMessage                             .2.12.16.4
--        evResetTrapnum                             .2.12.16.5
--        evResetClass                               .2.12.16.6
--      evGlobal                                     .2.12.18
--        evGlobalActions                            .2.12.18.1
--        evGlobalTrapnum                            .2.12.18.2
--    action                                         .2.14
--      actionSched                                  .2.14.3
--        actionSchedEnable                          .2.14.3.1
--        actionSchedBegin                           .2.14.3.2
--        actionSchedEnd                             .2.14.3.3
--        actionSchedWeekdaysOnly                    .2.14.3.4
--      actionAsentria                               .2.14.4
--        actionAsentriaRequireAck                   .2.14.4.1
--        actionAsentriaVersion                      .2.14.4.2
--        actionAsentriaTCPPort                      .2.14.4.3
--      actionHostTable                              .2.14.6
--        actionHostEntry                            .2.14.6.1
--          actionHostIndex                          .2.14.6.1.1
--          actionHost                               .2.14.6.1.2
--      actionEmailTable                             .2.14.7
--        actionEmailEntry                           .2.14.7.1
--          actionEmailIndex                         .2.14.7.1.1
--          actionEmail                              .2.14.7.1.2
--      actionParseError                             .2.14.8
--    sys                                            .2.16
--      sysTime                                      .2.16.1
--        sysTimeAutoDST                             .2.16.1.1
--        sysTimeGMTOffset                           .2.16.1.2
--        sysTimeGMTDirection                        .2.16.1.3
--        sysTimeNet                                 .2.16.1.4
--          sysTimeNetEnable                         .2.16.1.4.1
--          sysTimeNetHostTable                      .2.16.1.4.2
--            sysTimeNetHostEntry                    .2.16.1.4.2.1
--              sysTimeNetHostIndex                  .2.16.1.4.2.1.1
--              sysTimeNetHost                       .2.16.1.4.2.1.2
--      sysPT                                        .2.16.2
--        sysPTTimeout                               .2.16.2.1
--        sysPTEndPause                              .2.16.2.2
--      sysMTU                                       .2.16.3
--      sysAnswerString                              .2.16.4
--      sysEventFileID                               .2.16.6
--      sysEscapeCharacter                           .2.16.7
--      sysTimeStamp                                 .2.16.8
--        sysTimeStampTimeFormat                     .2.16.8.1
--        sysTimeStampDateFormat                     .2.16.8.2
--        sysTimeStampSpaceAfter                     .2.16.8.3
--      sysLog                                       .2.16.9
--        sysLogMode                                 .2.16.9.1
--        sysLoghost                                 .2.16.9.2
--        sysLogFilter                               .2.16.9.3
--        sysLogFileSize                             .2.16.9.4
--        sysLogFileCount                            .2.16.9.5
--        sysLogListenPort                           .2.16.9.6
--      sysCRDB                                      .2.16.10
--        sysCRDBCapacity                            .2.16.10.1
--        sysCRDBPercentFull                         .2.16.10.2
--        sysCRDBFileIDTable                         .2.16.10.3
--          sysCRDBFileIDEntry                       .2.16.10.3.1
--            sysCRDBFileIDIndex                     .2.16.10.3.1.1
--            sysCRDBFileID                          .2.16.10.3.1.2
--        sysCRDBFileEnforceMinTable                 .2.16.10.4
--          sysCRDBFileEnforceMinEntry               .2.16.10.4.1
--            sysCRDBFileEnforceMinIndex             .2.16.10.4.1.1
--            sysCRDBFileEnforceMin                  .2.16.10.4.1.2
--      sysCharMask                                  .2.16.11
--      sysPrompt                                    .2.16.12
--      sysBootStatus                                .2.16.13
--      sysLoc                                       .2.16.14
--        sysLocLatitude                             .2.16.14.1
--        sysLocLongitude                            .2.16.14.2
--        sysLocXOffset                              .2.16.14.3
--        sysLocYOffset                              .2.16.14.4
--        sysLocAngle                                .2.16.14.5
--        sysLocAltitude                             .2.16.14.6
--      sysFileTransfer                              .2.16.17
--        sysFileTransferStatus                      .2.16.17.1
--        sysFileTransferURL                         .2.16.17.2
--        sysFileTransferUsername                    .2.16.17.3
--        sysFileTransferPassword                    .2.16.17.4
--      sysUpdate                                    .2.16.18
--        sysUpdateStatus                            .2.16.18.1
--    auditLog                                       .2.17
--      auditLogEnable                               .2.17.1
--      auditLogStoreResets                          .2.17.2
--      auditLogStoreCommands                        .2.17.3
--      auditLogStoreRelays                          .2.17.4
--      auditLogStoreAlarmActions                    .2.17.5
--      auditLogStorePwdFailures                     .2.17.6
--      auditLogStoreLogins                          .2.17.7
--      auditLogStoreSHSK                            .2.17.8
--      auditLogStorePassthrough                     .2.17.9
--      auditLogStoreInactivity                      .2.17.10
--      auditLogStorePolling                         .2.17.11
--      auditLogMaxSize                              .2.17.12
--    scripting                                      .2.18
--      scrGlobalEnable                              .2.18.1
--      scrDTRCtrlPortEnableTable                    .2.18.2
--        scrDTRCtrlPortEnableEnabletry              .2.18.2.1
--          scrDTRCtrlPortEnableIndex                .2.18.2.1.1
--          scrDTRCtrlPortEnable                     .2.18.2.1.2
--      scrTable                                     .2.18.3
--        scrEntry                                   .2.18.3.1
--          scrIndex                                 .2.18.3.1.1
--          scrEnable                                .2.18.3.1.2
--          scrName                                  .2.18.3.1.3
--          scrFilename                              .2.18.3.1.4
--          scrRunAlways                             .2.18.3.1.5
--          scrRunAtStartup                          .2.18.3.1.6
--          scrRunScheduled                          .2.18.3.1.7
--          scrScheduleTime                          .2.18.3.1.8
--          scrArguments                             .2.18.3.1.9
--          scrRepeatInterval                        .2.18.3.1.10
--      scrVolatileStringTable                       .2.18.4
--        scrVolatileStringEntry                     .2.18.4.1
--          scrVolatileStringIndex                   .2.18.4.1.1
--          scrVolatileString                        .2.18.4.1.2
--      scrVolatileIntTable                          .2.18.5
--        scrVolatileIntEntry                        .2.18.5.1
--          scrVolatileIntIndex                      .2.18.5.1.1
--          scrVolatileInt                           .2.18.5.1.2
--      scrNonVolatileStringTable                    .2.18.6
--        scrNonVolatileStringEntry                  .2.18.6.1
--          scrNonVolatileStringIndex                .2.18.6.1.1
--          scrNonVolatileString                     .2.18.6.1.2
--      scrNonVolatileIntTable                       .2.18.7
--        scrNonVolatileIntEntry                     .2.18.7.1
--          scrNonVolatileIntIndex                   .2.18.7.1.1
--          scrNonVolatileInt                        .2.18.7.1.2
--    generator                                      .2.19
--      genSet                                       .2.19.1
--        genSetEnable                               .2.19.1.1
--        genSetRelay                                .2.19.1.2
--          genSetRelayEs                            .2.19.1.2.1
--          genSetRelayPoint                         .2.19.1.2.2
--          genSetRelayRunningstate                  .2.19.1.2.3
--        genSetCc                                   .2.19.1.3
--          genSetCcEnable                           .2.19.1.3.1
--          genSetCcEs                               .2.19.1.3.2
--          genSetCcPoint                            .2.19.1.3.3
--          genSetCcRunningstate                     .2.19.1.3.4
--      genRun                                       .2.19.2
--        genRunMode                                 .2.19.2.1
--        genRunSched                                .2.19.2.2
--        genRunDuration                             .2.19.2.3
--        genRunForce                                .2.19.2.4
--        genRunReqasm                               .2.19.2.5
--        genRunStatus                               .2.19.2.6
--        genRunNonstartEvent                        .2.19.2.7
--          genRunNonstartEventEnable                .2.19.2.7.1
--          genRunNonstartEventActions               .2.19.2.7.2
--          genRunNonstartEventTrap                  .2.19.2.7.3
--          genRunNonstartEventClass                 .2.19.2.7.4
--    calendar                                       .2.20
--      schedTable                                   .2.20.1
--        schedEntry                                 .2.20.1.1
--          schedIndex                               .2.20.1.1.1
--          schedEnable                              .2.20.1.1.2
--          schedStart                               .2.20.1.1.3
--          schedRepeatMode                          .2.20.1.1.4
--          schedRepeatFreq                          .2.20.1.1.5
--          schedRepeatEndMode                       .2.20.1.1.6
--          schedRepeatEndAfter                      .2.20.1.1.7
--          schedRepeatEndOn                         .2.20.1.1.8
--          schedRepeatWeeklySun                     .2.20.1.1.9
--          schedRepeatWeeklyMon                     .2.20.1.1.10
--          schedRepeatWeeklyTue                     .2.20.1.1.11
--          schedRepeatWeeklyWed                     .2.20.1.1.12
--          schedRepeatWeeklyThu                     .2.20.1.1.13
--          schedRepeatWeeklyFri                     .2.20.1.1.14
--          schedRepeatWeeklySat                     .2.20.1.1.15
--          schedRepeatMonthlyMode                   .2.20.1.1.16
--          schedRepeatMonthlyDates                  .2.20.1.1.17
--          schedRepeatMonthlyOnThe                  .2.20.1.1.18
--          schedRepeatMonthlyOnDay                  .2.20.1.1.19
--          schedRepeatYearlyJan                     .2.20.1.1.20
--          schedRepeatYearlyFeb                     .2.20.1.1.21
--          schedRepeatYearlyMar                     .2.20.1.1.22
--          schedRepeatYearlyApr                     .2.20.1.1.23
--          schedRepeatYearlyMay                     .2.20.1.1.24
--          schedRepeatYearlyJun                     .2.20.1.1.25
--          schedRepeatYearlyJul                     .2.20.1.1.26
--          schedRepeatYearlyAug                     .2.20.1.1.27
--          schedRepeatYearlySep                     .2.20.1.1.28
--          schedRepeatYearlyOct                     .2.20.1.1.29
--          schedRepeatYearlyNov                     .2.20.1.1.30
--          schedRepeatYearlyDec                     .2.20.1.1.31
--          schedRepeatYearlyOnThe                   .2.20.1.1.32
--          schedRepeatYearlyOnDay                   .2.20.1.1.33
--          schedNextTrigger                         .2.20.1.1.34

--  productIds                                       .3
--    siteName                                        3.1
--    thisProduct                                    .3.2
--    stockTrapString                                .3.3
--    trapEventTypeNumber                            .3.4
--    trapEventTypeName                              .3.5
--    trapIncludedValue                              .3.6
--    trapIncludedString                             .3.7
--    trapTypeString                                 .3.8
--    trapEventClassNumber                           .3.9
--    trapEventClassName                             .3.10

--  keyInterface                                     .4.0


--***************************************************************************************
--TOP-LEVEL OBJECT IDENTIFIERS
--***************************************************************************************



    s450notifications OBJECT IDENTIFIER ::= { s450 0 }
    --1.3.6.1.4.1.3052.17.0

    status OBJECT IDENTIFIER ::= { s450 1 }
    --1.3.6.1.4.1.3052.17.1

        eventSensorStatus OBJECT IDENTIFIER ::= { status 1 }
        --1.3.6.1.4.1.3052.17.1.1

        dataEventStatus OBJECT IDENTIFIER ::= { status 2 }
        --1.3.6.1.4.1.3052.17.1.2

        fuelSensorStatus OBJECT IDENTIFIER ::= { status 6 }
        --1.3.6.1.4.1.3052.17.1.6

        wirelessModemStatus OBJECT IDENTIFIER ::= { status 7 }
        --1.3.6.1.4.1.3052.17.1.7

        acPowerMonitorStatus OBJECT IDENTIFIER ::= { status 8 }
        --1.3.6.1.4.1.3052.17.1.8

        batteryMonitorStatus OBJECT IDENTIFIER ::= { status 10 }
        --1.3.6.1.4.1.3052.17.1.10


    config OBJECT IDENTIFIER ::= { s450 2 }
    --1.3.6.1.4.1.3052.17.2

        eventSensorBasics OBJECT IDENTIFIER ::= { config 1 }
        --1.3.6.1.4.1.3052.17.2.1

        eventSensorPointConfig OBJECT IDENTIFIER ::= { config 2 }
        --1.3.6.1.4.1.3052.17.2.2

        serialPorts OBJECT IDENTIFIER ::= { config 3 }
        --1.3.6.1.4.1.3052.17.2.3

        network OBJECT IDENTIFIER ::= { config 4 }
        --1.3.6.1.4.1.3052.17.2.4

            interface OBJECT IDENTIFIER ::= { network 1 }
            --1.3.6.1.4.1.3052.17.2.4

                ethernet OBJECT IDENTIFIER ::= { interface 1 }
                --1.3.6.1.4.1.3052.17.2.4.1

                    ethernet1 OBJECT IDENTIFIER ::= { ethernet 1 }
                    --1.3.6.1.4.1.3052.17.2.4.1.1

                        eth1VLAN OBJECT IDENTIFIER ::= { ethernet1 5 }
                        --1.3.6.1.4.1.3052.17.2.4.1.1.5

                            eth1VLAN1 OBJECT IDENTIFIER ::= { eth1VLAN 1 }
                            --1.3.6.1.4.1.3052.17.2.4.1.1.5.1

                            eth1VLAN2 OBJECT IDENTIFIER ::= { eth1VLAN 2 }
                            --1.3.6.1.4.1.3052.17.2.4.1.1.5.2

                            eth1VLAN3 OBJECT IDENTIFIER ::= { eth1VLAN 3 }
                            --1.3.6.1.4.1.3052.17.2.4.1.1.5.3

                            eth1VLAN4 OBJECT IDENTIFIER ::= { eth1VLAN 4 }
                            --1.3.6.1.4.1.3052.17.2.4.1.1.5.4

                            eth1VLAN5 OBJECT IDENTIFIER ::= { eth1VLAN 5 }
                            --1.3.6.1.4.1.3052.17.2.4.1.1.5.5

                            eth1VLAN6 OBJECT IDENTIFIER ::= { eth1VLAN 6 }
                            --1.3.6.1.4.1.3052.17.2.4.1.1.5.6

                    ethernet2 OBJECT IDENTIFIER ::= { ethernet 2 }
                    --1.3.6.1.4.1.3052.17.2.4.1.2

                        eth2VLAN OBJECT IDENTIFIER ::= { ethernet2 5 }
                        --1.3.6.1.4.1.3052.17.2.4.1.2.5

                            eth2VLAN1 OBJECT IDENTIFIER ::= { eth2VLAN 1 }
                            --1.3.6.1.4.1.3052.17.2.4.1.2.5.1

                            eth2VLAN2 OBJECT IDENTIFIER ::= { eth2VLAN 2 }
                            --1.3.6.1.4.1.3052.17.2.4.1.2.5.2

                            eth2VLAN3 OBJECT IDENTIFIER ::= { eth2VLAN 3 }
                            --1.3.6.1.4.1.3052.17.2.4.1.2.5.3

                            eth2VLAN4 OBJECT IDENTIFIER ::= { eth2VLAN 4 }
                            --1.3.6.1.4.1.3052.17.2.4.1.2.5.4

                            eth2VLAN5 OBJECT IDENTIFIER ::= { eth2VLAN 5 }
                            --1.3.6.1.4.1.3052.17.2.4.1.2.5.5

                            eth2VLAN6 OBJECT IDENTIFIER ::= { eth2VLAN 6 }
                            --1.3.6.1.4.1.3052.17.2.4.1.2.5.6

            snmp OBJECT IDENTIFIER ::= { network 8 }
            --1.3.6.1.4.1.3052.17.2.4.8

                snmpNotificationTx OBJECT IDENTIFIER ::= { snmp 7 }
                --1.3.6.1.4.1.3052.17.2.4.8.7

                snmpProxy OBJECT IDENTIFIER ::= { snmp 8 }
                --1.3.6.1.4.1.3052.17.2.4.8.8

                snmpPoll OBJECT IDENTIFIER ::= { snmp 9 }
                --1.3.6.1.4.1.3052.17.2.4.8.9

            ftpPush OBJECT IDENTIFIER ::= { network 9 }
            --1.3.6.1.4.1.3052.17.2.4.9

            routing OBJECT IDENTIFIER ::= { network 11 }
            --1.3.6.1.4.1.3052.17.2.4.11

            netSecurity OBJECT IDENTIFIER ::= { network 12 }
            --1.3.6.1.4.1.3052.17.2.4.12

                ipRestriction OBJECT IDENTIFIER ::= { netSecurity 1 }
                --1.3.6.1.4.1.3052.17.2.4.12.1

            rts OBJECT IDENTIFIER ::= { network 13 }
            --1.3.6.1.4.1.3052.17.2.4.13

                rtsAlarms OBJECT IDENTIFIER ::= { rts 2 }
                --1.3.6.1.4.1.3052.17.2.4.13.2

            trap OBJECT IDENTIFIER ::= { network 14 }
            --1.3.6.1.4.1.3052.17.2.4.14

                trapInclude OBJECT IDENTIFIER ::= { trap 1}
                --1.3.6.1.4.1.3052.17.2.4.14.1

            wireless OBJECT IDENTIFIER ::= { network 16 }
            --1.3.6.1.4.1.3052.17.2.4.16

            email OBJECT IDENTIFIER ::= { network 17 }
            --1.3.6.1.4.1.3052.17.2.4.17

            netAdvanced OBJECT IDENTIFIER ::= { network 18 }
            --1.3.6.1.4.1.3052.17.2.4.18

            web OBJECT IDENTIFIER ::= { network 19 }
            --1.3.6.1.4.1.3052.17.2.4.19

        time OBJECT IDENTIFIER ::= { config 8 }
        --1.3.6.1.4.1.3052.17.2.8

        console OBJECT IDENTIFIER ::= { config 10 }
        --1.3.6.1.4.1.3052.17.2.10

        unitSecurity OBJECT IDENTIFIER ::= { config 11 }
        --1.3.6.1.4.1.3052.17.2.11

            secCore OBJECT IDENTIFIER ::= { unitSecurity 1 }
            --1.3.6.1.4.1.3052.17.2.11.1

            secFactory OBJECT IDENTIFIER ::= { unitSecurity 3 }
            --1.3.6.1.4.1.3052.17.2.11.3

        event OBJECT IDENTIFIER ::= { config 12 }
        --1.3.6.1.4.1.3052.17.2.12

            evCore OBJECT IDENTIFIER ::= { event 1 }
            --1.3.6.1.4.1.3052.17.2.12.1

                evLog OBJECT IDENTIFIER ::= { evCore 3 }
                --1.3.6.1.4.1.3052.17.2.12.1.3

                evMgmt OBJECT IDENTIFIER ::= { evCore 4 }
                --1.3.6.1.4.1.3052.17.2.12.1.4

            evSched1 OBJECT IDENTIFIER ::= { event 5 }
            --1.3.6.1.4.1.3052.17.2.12.5

            evSched2 OBJECT IDENTIFIER ::= { event 6 }
            --1.3.6.1.4.1.3052.17.2.12.6

            evNoSensor OBJECT IDENTIFIER ::= { event 9 }
            --1.3.6.1.4.1.3052.17.2.12.9

            fuelSensor OBJECT IDENTIFIER ::= { event 11 }
            --1.3.6.1.4.1.3052.17.2.12.11

            acPowerMonitor OBJECT IDENTIFIER ::= { event 12 }
            --1.3.6.1.4.1.3052.17.2.12.12

            batteryMonitor OBJECT IDENTIFIER ::= { event 14 }
            --1.3.6.1.4.1.3052.17.2.12.14

            evReset OBJECT IDENTIFIER ::= { event 16 }
            --1.3.6.1.4.1.3052.17.2.12.16

            evGlobal OBJECT IDENTIFIER ::= { event 18 }
            --1.3.6.1.4.1.3052.17.2.12.18

        action OBJECT IDENTIFIER ::= { config 14 }
        --1.3.6.1.4.1.3052.17.2.14

            actionSched OBJECT IDENTIFIER ::= { action 3 }
            --1.3.6.1.4.1.3052.17.2.14.3

            actionAsentria OBJECT IDENTIFIER ::= { action 4 }
            --1.3.6.1.4.1.3052.17.2.14.4

        sys OBJECT IDENTIFIER ::= { config 16 }
        --1.3.6.1.4.1.3052.17.2.16

            sysTime OBJECT IDENTIFIER ::= { sys 1 }
            --1.3.6.1.4.1.3052.17.2.16.1

                sysTimeNet OBJECT IDENTIFIER ::= { sysTime 4 }
                --1.3.6.1.4.1.3052.17.2.16.1.4

            sysPT OBJECT IDENTIFIER ::= { sys 2 }
            --1.3.6.1.4.1.3052.17.2.16.2

            sysTimeStamp OBJECT IDENTIFIER ::= { sys 8 }
            --1.3.6.1.4.1.3052.17.2.16.8

            sysLog OBJECT IDENTIFIER ::= { sys 9 }
            --1.3.6.1.4.1.3052.17.2.16.9

            sysCRDB OBJECT IDENTIFIER ::= { sys 10 }
            --1.3.6.1.4.1.3052.17.2.16.10

            sysLoc OBJECT IDENTIFIER ::= { sys 14 }
            --1.3.6.1.4.1.3052.17.2.16.14

            sysFileTransfer OBJECT IDENTIFIER ::= { sys 17 }
            --1.3.6.1.4.1.3052.17.2.16.17

            sysUpdate OBJECT IDENTIFIER ::= { sys 18 }
            --1.3.6.1.4.1.3052.17.2.16.18

        auditLog OBJECT IDENTIFIER ::= { config 17 }
        --1.3.6.1.4.1.3052.17.2.17

        scripting OBJECT IDENTIFIER ::= { config 18 }
        --1.3.6.1.4.1.3052.17.2.18

        generator OBJECT IDENTIFIER ::= { config 19 }
        --1.3.6.1.4.1.3052.17.2.19

          genSet OBJECT IDENTIFIER ::= { generator 1 }
          --1.3.6.1.4.1.3052.17.2.19.1

            genSetRelay OBJECT IDENTIFIER ::= { genSet 2 }
            --1.3.6.1.4.1.3052.17.2.19.1.2

            genSetCC OBJECT IDENTIFIER ::= { genSet 3 }
            --1.3.6.1.4.1.3052.17.2.19.1.3

          genRun OBJECT IDENTIFIER ::= { generator 2 }
          --1.3.6.1.4.1.3052.17.2.19.2

            genRunNonstartEvent OBJECT IDENTIFIER ::= { genRun 7 }
            --1.3.6.1.4.1.3052.17.2.19.2.7

        calendar OBJECT IDENTIFIER ::= { config 20 }
        --1.3.6.1.4.1.3052.17.2.20

    productIds OBJECT IDENTIFIER ::= { s450 3 }
    --1.3.6.1.4.1.3052.17.3

--***************************************************************************************
--OBJECT DEFINITIONS
--***************************************************************************************

--***************************************************************************************
--EventSensor Status Section    1.1
--***************************************************************************************

esPointTable OBJECT-TYPE
    SYNTAX SEQUENCE OF ESPoint
    MAX-ACCESS not-accessible
    STATUS current
    DESCRIPTION
        "
        This table organizes 4 basic attributes of points.  A point
        is a particular sensor on an EventSensor (e.g., temperature,
        humidity, contact closure 2, relay 5, etc.).  The 4 point
        attributes are its name, whether it's in its event state,
        the point's value as a number and its value as a string.

        Points are referenced by a point index.  The point index
        is a string of 3 numbers separated by periods.
        It contains all the information necessary for getting a piece
        of data off an event sensor; namely, which EventSensor,
        point class, and which-sensor-of-that-class (a.k.a. point).
        "
    ::= { eventSensorStatus 1 }
    --1.3.6.1.4.1.3052.17.1.1.1

esPointEntry OBJECT-TYPE
    SYNTAX ESPoint
    MAX-ACCESS not-accessible
    STATUS current
    DESCRIPTION
        "Entry for EventSensor point table"
    INDEX { esIndexES, esIndexPC, esIndexPoint }
    ::= { esPointTable 1 }
    --1.3.6.1.4.1.3052.17.1.1.1.1

esIndexES OBJECT-TYPE
    SYNTAX Integer32 (1..200)
    MAX-ACCESS read-only
    STATUS current
    DESCRIPTION
        "The part of the point index that refers to an
        EventSensor.

        The point index is a string of 3 numbers separated
        by periods.  It contains all the information
        necessary for getting a piece of data off an event
        sensor; namely, which EventSensor, point class,
        and which-sensor-of-that-class (a.k.a. point).

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndexES=2
        will now refer to that particular EventSensor.
        "
    ::= { esPointEntry 1 }
    --1.3.6.1.4.1.3052.17.1.1.1.1.1

esIndexPC OBJECT-TYPE
    SYNTAX Integer32 (1..6)
    MAX-ACCESS read-only
    STATUS current
    DESCRIPTION
        "The part of the point index that refers to point class.

        The point index is a string of 3 numbers separated by periods.
        It contains all the information necessary for getting a piece
        of data off an event sensor; namely, which EventSensor,
        point class, and which-sensor-of-that-class (a.k.a. point).

        The values for this object are:
        1=temperature sensor
        2=contact closure
        3=humidity sensor
        4=noise sensor
        5=analog input
        6=relay
        "
    ::= { esPointEntry 2 }
    --1.3.6.1.4.1.3052.17.1.1.1.1.2

esIndexPoint OBJECT-TYPE
    SYNTAX Integer32 (1..64)
    MAX-ACCESS read-only
    STATUS current
    DESCRIPTION
        "The part of the point index that delineates which
        sensor on the EventSensor.

        So this combined with esIndexPC (Point Class or type)
        and esIndexES (which EventSensor) uniquely defines each
        point (sensor or relay) attached to a unit.  For
        example, if esIndexES is 3, esIndexPC is 1 and
        esIndexPoint is 4 then this is the Fourth Temperature
        Sensor on EventSensor number 3."
    ::= { esPointEntry 3 }
    --1.3.6.1.4.1.3052.17.1.1.1.1.3

esPointName OBJECT-TYPE
    SYNTAX DisplayString
    MAX-ACCESS read-write
    STATUS current
    DESCRIPTION
        "The name of the point on an EventSensor. For example,
        'AC temp' (in the case of the temperature sensor on an
        EventSensor).

        There can be multiple points of the same point class on an
        EventSensor (e.g., 8 contact closures) and multiple sensor
        classes on an EventSensor (e.g., temperature, contact closure,
        humidity).

        If the point referenced by a given point index is solitary
        (e.g., temperature sensor, because there can be only one on
        an EventSensor), then this object reads as '<EventSensor
        name>'.  Setting this object for solitary point indices sets
        the EventSensor name only.

        On the other hand, if a given point is among other points of
        the same point class on an EventSensor, then this object reads
        as '<Sensor name>'.  Setting this object for these NON-
        solitary point indices sets the sensor name only - not the
        EventSensor name."
    ::= { esPointEntry 4 }
    --1.3.6.1.4.1.3052.17.1.1.1.1.4

esPointInEventState OBJECT-TYPE
    SYNTAX Integer32
    MAX-ACCESS read-write
    STATUS current
    DESCRIPTION
        "A number referring to the event state of a point
        on an EventSensor.  This number can have different
        meanings depending on the point class.

        If the point class is temperature, humidity, or
        analog input, then the values of this object are:
        1=very low
        2=low
        3=normal
        4=high
        5=very high

        For contact closures the values of this object are:
        1=point in event state
        2=point in normal state

        For relays the values of this object are:
        1=relay energized (active)
        2=relay de-energized (inactive)

        For any point class and any point, if the event
        state is undefined, then the value of this object
        is 0.

        For any point class except relay, this object is
        read-only.  For relays, setting this object to 1
        puts the relay into its active (energized) state.
        Setting it to 2 puts the relay into its inactive
        (de-energized) state.  Setting it to any
        value greater than 2 puts the relay into its
        active state for that many seconds (up to 3600),
        after which time it puts the relay into its
        inactive state.
        "
    ::= { esPointEntry 5 }
    --1.3.6.1.4.1.3052.17.1.1.1.1.5

esPointValueInt OBJECT-TYPE
    SYNTAX Integer32 (-2147483648..2147483647)
    MAX-ACCESS read-write
    STATUS current
    DESCRIPTION
        "A read-only number referring to the value of a
        point on an EventSensor.

        If the point class is temperature, then this object
        is the temperature in its configured scale (default
        is Fahrenheit).

        If the point class is contact closure or relay, then
        this object is either 0 (open) or 1 (closed).

        If the point class is humidity, then this object
        is the percent relative humidity.

        If the point class is analog input, then this
        object is the signed input value in tenths of the
        configured units.

        If the point class is relay, then this object is
        either 1 (active a.k.a. energized) or 0
        (inactive a.k.a. de-energized).  This object cannot
        be used to control the relay (use esPointInEventState
        for that).
        "
    ::= { esPointEntry 6 }
    --1.3.6.1.4.1.3052.17.1.1.1.1.6

esPointValueStr OBJECT-TYPE
    SYNTAX DisplayString
    MAX-ACCESS read-only
    STATUS current
    DESCRIPTION
        "A string referring to the value of a point on an
        EventSensor.

        For contact closures this object is either 'Open'
        or 'Closed'.

        For relays this object is either 'Active'
        (energized) or 'Inactive' (de-energized).

        For temperature and humidity point classes, this
        object is the string representation of the
        esPointValueInt object.  For temperature, 'C' or
        'F' is including in the string to indicate scale.

        For analog inputs, this object is the string
        representation of the plus/minus input in the
        configured units appended with the unit name.
        "
    ::= { esPointEntry 7 }
    --1.3.6.1.4.1.3052.17.1.1.1.1.7

esPointTimeLastChange OBJECT-TYPE
    SYNTAX DisplayString
    MAX-ACCESS read-only
    STATUS current
    DESCRIPTION
        "The time of the last time an event was
        triggerred for a point on an EventSensor in
        MM/DD/YY HH:MM:SS format.

        For contact closures, the possible events are
        Active and Inactive.  For temperature, humidity,
        and analog inputs, the possible events are Normal,
        High, Very High, Low, and Very Low.

        For relays, this object is a null string."
    ::= { esPointEntry 8 }
    --1.3.6.1.4.1.3052.17.1.1.1.1.8

esPointTimetickLastChange OBJECT-TYPE
    SYNTAX TimeTicks
    MAX-ACCESS read-only
    STATUS current
    DESCRIPTION
        "The time of the last time an event was
        triggerred for a point on an EventSensor in
        100ths of seconds since reset.

        For contact closures, the possible events are
        Active and Inactive.  For temperature, humidity,
        and analog inputs, the possible events are Normal,
        High, Very High, Low, and Very Low.

        For relays, this object is 0."
    ::= { esPointEntry 9 }
    --1.3.6.1.4.1.3052.17.1.1.1.1.9


esPointAliasValueStr OBJECT-TYPE
    SYNTAX DisplayString
    MAX-ACCESS read-only
    STATUS current
    DESCRIPTION
        "For CC inputs, this is the CC active/inactive alias setting
         setting value that currently corresponds to the event state.
         So if the CC input is in the event state, then this object
         is the active alias setting value.  If the CC input is in the
         normal state, then this object is the inactive alias setting
         value.

         For relay/power outputs, this is the output active/inactive
         alias setting value that currently corresponds to the output
         state.  So if the output is in the active state, then this
         object is the active alias setting value.  If the output is
         in hte inactive state, then this object is the inactive alias
         setting value.

         For non-CC and non-output sensors, this is the same as the
         esPointValueStr object."
    ::= { esPointEntry 10 }
    --1.3.6.1.4.1.3052.17.1.1.1.1.10

--***************************************************************************************
--Data Event Status Section 1.2
--***************************************************************************************

deStatusTable OBJECT-TYPE
    SYNTAX SEQUENCE OF DEStatus
    MAX-ACCESS not-accessible
    STATUS current
    DESCRIPTION
        "Data Event Status Table"
    ::= { dataEventStatus 1 }
    --1.3.6.1.4.1.3052.17.1.2.1

deStatusEntry OBJECT-TYPE
    SYNTAX DEStatus
    MAX-ACCESS not-accessible
    STATUS current
    DESCRIPTION
        "EventSensor status entry"
    INDEX { deStatusIndex }
    ::= { deStatusTable 1 }
    --1.3.6.1.4.1.3052.17.1.2.1.1

deStatusIndex OBJECT-TYPE
    SYNTAX Integer32 (1..100)
    MAX-ACCESS read-only
    STATUS current
    DESCRIPTION
        "Index for Data Events"
    ::= { deStatusEntry 1 }
    --1.3.6.1.4.1.3052.17.1.2.1.1.1

deStatusName OBJECT-TYPE
    SYNTAX DisplayString
    MAX-ACCESS read-only
    STATUS current
    DESCRIPTION
        "Data Event name"
    ::= { deStatusEntry 2 }
    --1.3.6.1.4.1.3052.17.1.2.1.1.2

deStatusCounter OBJECT-TYPE
    SYNTAX Integer32
    MAX-ACCESS read-only
    STATUS current
    DESCRIPTION
        "Number of times a data record has matched this
        event's equation.
        Range: 1-999999999"
    ::= { deStatusEntry 3 }
    --1.3.6.1.4.1.3052.17.1.2.1.1.3

deStatusThreshold OBJECT-TYPE
    SYNTAX Integer32
    MAX-ACCESS read-only
    STATUS current
    DESCRIPTION
        "Number of times the equation is matched before
        an event is triggered.
        Range: 1-999999999"
    ::= { deStatusEntry 4 }
    --1.3.6.1.4.1.3052.17.1.2.1.1.4


--***************************************************************************************
--Fuel Sensor 1.5
--***************************************************************************************

fsStatusTable OBJECT-TYPE
    SYNTAX SEQUENCE OF FSStatus
    MAX-ACCESS not-accessible
    STATUS current
    DESCRIPTION
        "Fuel sensor status table"
    ::= { fuelSensorStatus 1 }
    --1.3.6.1.4.1.3052.17.1.6.1

fsStatusEntry OBJECT-TYPE
    SYNTAX FSStatus
    MAX-ACCESS not-accessible
    STATUS current
    DESCRIPTION
        "Fuel sensor status table entry"
    INDEX { fsStatusIndex }
    ::= { fsStatusTable 1 }
    --1.3.6.1.4.1.3052.17.1.6.1.1

fsStatusIndex OBJECT-TYPE
    SYNTAX Integer32 (1..3)
    MAX-ACCESS read-only
    STATUS current
    DESCRIPTION
        "Index for fuel sensors"
    ::= { fsStatusEntry 1 }
    --1.3.6.1.4.1.3052.17.1.6.1.1.1

fsStatusName OBJECT-TYPE
    SYNTAX DisplayString
    MAX-ACCESS read-only
    STATUS current
    DESCRIPTION
        "Fuel sensor name"
    ::= { fsStatusEntry 2 }
    --1.3.6.1.4.1.3052.17.1.6.1.1.2

fsStatusDeviceState OBJECT-TYPE
    SYNTAX DisplayString
    MAX-ACCESS read-only
    STATUS current
    DESCRIPTION
        "Fuel sensor device state"
    ::= { fsStatusEntry 3 }
    --1.3.6.1.4.1.3052.17.1.6.1.1.3

fsStatusVolumeValueString OBJECT-TYPE
    SYNTAX DisplayString
    MAX-ACCESS read-only
    STATUS current
    DESCRIPTION
        "Fuel volume. Range is -2,147,483,648 to 2,147,483,647. This value reads
         -999 when the fuel sensor is disconnected"
    ::= { fsStatusEntry 4 }
    --1.3.6.1.4.1.3052.17.1.6.1.1.4

fsStatusVolumePercentLevel OBJECT-TYPE
    SYNTAX DisplayString
    MAX-ACCESS read-only
    STATUS current
    DESCRIPTION
        "Height of the fluid in the tank expressed as a percentage of the tank
         height, in hundredths of a percent."
    ::= { fsStatusEntry 7 }
    --1.3.6.1.4.1.3052.17.1.6.1.1.7

fsStatusVolumeInEventState OBJECT-TYPE
    SYNTAX DisplayString
    MAX-ACCESS read-only
    STATUS current
    DESCRIPTION
        "Current event status of the fuel sensor."
    ::= { fsStatusEntry 8 }
    --1.3.6.1.4.1.3052.17.1.6.1.1.8

fsStatusCombined OBJECT-TYPE
    SYNTAX DisplayString
    MAX-ACCESS read-only
    STATUS current
    DESCRIPTION
        "Combined status string intended to be parsed by NMS:
        deviceState`deviceStateColorCode`percentRounded`valueAsFloat`volumeEventState`volumeEventStateColorCode`capacity`units`name"
    ::= { fsStatusEntry 9 }
    --1.3.6.1.4.1.3052.17.1.6.1.1.9

--***************************************************************************************
--Wireless Modem Status Section  1.7
--***************************************************************************************

wmsStatus OBJECT-TYPE
    SYNTAX DisplayString
    MAX-ACCESS read-only
    STATUS current
    DESCRIPTION
        "Wireless modem status"
    ::= { wirelessModemStatus 1 }
    --1.3.6.1.4.1.3052.17.1.7.1

wmsSignal OBJECT-TYPE
    SYNTAX DisplayString
    MAX-ACCESS read-only
    STATUS current
    DESCRIPTION
        "Wireless modem Signal strength"
    ::= { wirelessModemStatus 2 }
    --1.3.6.1.4.1.3052.17.1.7.2

wmsRSSI OBJECT-TYPE
    SYNTAX DisplayString
    MAX-ACCESS read-only
    STATUS current
    DESCRIPTION
        "Wireless modem Signal strength (RSSI)"
    ::= { wirelessModemStatus 3 }
    --1.3.6.1.4.1.3052.17.1.7.3

wmsBER OBJECT-TYPE
    SYNTAX DisplayString
    MAX-ACCESS read-only
    STATUS current
    DESCRIPTION
        "Wireless modem Bit Error Rate"
    ::= { wirelessModemStatus 4 }
    --1.3.6.1.4.1.3052.17.1.7.4

wmsUpdated OBJECT-TYPE
    SYNTAX DisplayString
    MAX-ACCESS read-only
    STATUS current
    DESCRIPTION
        "Wireless modem info last update time"
    ::= { wirelessModemStatus 5 }
    --1.3.6.1.4.1.3052.17.1.7.5

wmsRegistration OBJECT-TYPE
    SYNTAX DisplayString
    MAX-ACCESS read-only
    STATUS current
    DESCRIPTION
        "Wireless modem registration status"
    ::= { wirelessModemStatus 6 }
    --1.3.6.1.4.1.3052.17.1.7.6

wmsLAC OBJECT-TYPE
    SYNTAX DisplayString
    MAX-ACCESS read-only
    STATUS current
    DESCRIPTION
        "Wireless modem Location Area Code"
    ::= { wirelessModemStatus 7 }
    --1.3.6.1.4.1.3052.17.1.7.7

wmsCellID OBJECT-TYPE
    SYNTAX DisplayString
    MAX-ACCESS read-only
    STATUS current
    DESCRIPTION
        "Wireless modem Cell ID"
    ::= { wirelessModemStatus 8 }
    --1.3.6.1.4.1.3052.17.1.7.8

wmsIMSI OBJECT-TYPE
    SYNTAX DisplayString
    MAX-ACCESS read-only
    STATUS current
    DESCRIPTION
        "Wireless modem Internation Mobile Subscriber Identity number"
    ::= { wirelessModemStatus 9 }
    --1.3.6.1.4.1.3052.17.1.7.9

wmsPhnum OBJECT-TYPE
    SYNTAX DisplayString
    MAX-ACCESS read-only
    STATUS current
    DESCRIPTION
        "Wireless modem phone number"
    ::= { wirelessModemStatus 10 }
    --1.3.6.1.4.1.3052.17.1.7.10

wmsLocalIP OBJECT-TYPE
    SYNTAX DisplayString
    MAX-ACCESS read-only
    STATUS current
    DESCRIPTION
        "Local IP address of modem on wireless network"
    ::= { wirelessModemStatus 11 }
    --1.3.6.1.4.1.3052.17.1.7.11

wmsMgfID OBJECT-TYPE
    SYNTAX DisplayString
    MAX-ACCESS read-only
    STATUS current
    DESCRIPTION
        "Wireless modem manufacturer ID"
    ::= { wirelessModemStatus 12 }
    --1.3.6.1.4.1.3052.17.1.7.12

wmsModelID OBJECT-TYPE
    SYNTAX DisplayString
    MAX-ACCESS read-only
    STATUS current
    DESCRIPTION
        "Wireless modem model ID"
    ::= { wirelessModemStatus 13 }
    --1.3.6.1.4.1.3052.17.1.7.13

wmsIMEI OBJECT-TYPE
    SYNTAX DisplayString
    MAX-ACCESS read-only
    STATUS current
    DESCRIPTION
        "Wireless modem International Mobile Equipment Identity number"
    ::= { wirelessModemStatus 14 }
    --1.3.6.1.4.1.3052.17.1.7.14

wmsRevID OBJECT-TYPE
    SYNTAX DisplayString
    MAX-ACCESS read-only
    STATUS current
    DESCRIPTION
        "Wireless modem revision ID"
    ::= { wirelessModemStatus 15 }
    --1.3.6.1.4.1.3052.17.1.7.15

wmsNetName OBJECT-TYPE
    SYNTAX DisplayString
    MAX-ACCESS read-only
    STATUS current
    DESCRIPTION
        "Wireless modem network name"
    ::= { wirelessModemStatus 16 }
    --1.3.6.1.4.1.3052.17.1.7.16

wmsGPRSStatus OBJECT-TYPE
    SYNTAX DisplayString
    MAX-ACCESS read-only
    STATUS current
    DESCRIPTION
        "Wireless modem (E)GPRS status"
    ::= { wirelessModemStatus 17 }
    --1.3.6.1.4.1.3052.17.1.7.17

wmsBand OBJECT-TYPE
    SYNTAX DisplayString
    MAX-ACCESS read-only
    STATUS current
    DESCRIPTION
        "Wireless modem band"
    ::= { wirelessModemStatus 18 }
    --1.3.6.1.4.1.3052.17.1.7.18

wmsChannel OBJECT-TYPE
    SYNTAX DisplayString
    MAX-ACCESS read-only
    STATUS current
    DESCRIPTION
        "Wireless modem channel"
    ::= { wirelessModemStatus 19 }
    --1.3.6.1.4.1.3052.17.1.7.19

wmsCountryCode OBJECT-TYPE
    SYNTAX DisplayString
    MAX-ACCESS read-only
    STATUS current
    DESCRIPTION
        "Wireless modem country code"
    ::= { wirelessModemStatus 20 }
    --1.3.6.1.4.1.3052.17.1.7.20

wmsNetCode OBJECT-TYPE
    SYNTAX DisplayString
    MAX-ACCESS read-only
    STATUS current
    DESCRIPTION
        "Wireless modem network code"
    ::= { wirelessModemStatus 21 }
    --1.3.6.1.4.1.3052.17.1.7.21

wmsPLMNColor OBJECT-TYPE
    SYNTAX DisplayString
    MAX-ACCESS read-only
    STATUS current
    DESCRIPTION
        "Wireless modem PLMN color"
    ::= { wirelessModemStatus 22 }
    --1.3.6.1.4.1.3052.17.1.7.22

wmsBScolor OBJECT-TYPE
    SYNTAX DisplayString
    MAX-ACCESS read-only
    STATUS current
    DESCRIPTION
        "Wireless modem BS color"
    ::= { wirelessModemStatus 23 }
    --1.3.6.1.4.1.3052.17.1.7.23

wmsMpRACH OBJECT-TYPE
    SYNTAX DisplayString
    MAX-ACCESS read-only
    STATUS current
    DESCRIPTION
        "Wireless modem max power RACH"
    ::= { wirelessModemStatus 24 }
    --1.3.6.1.4.1.3052.17.1.7.24

wmsMinRxLevel OBJECT-TYPE
    SYNTAX DisplayString
    MAX-ACCESS read-only
    STATUS current
    DESCRIPTION
        "Wireless modem minimum receive level"
    ::= { wirelessModemStatus 25 }
    --1.3.6.1.4.1.3052.17.1.7.25

wmsBaseCoeff OBJECT-TYPE
    SYNTAX DisplayString
    MAX-ACCESS read-only
    STATUS current
    DESCRIPTION
        "Wireless modem base coefficient"
    ::= { wirelessModemStatus 26 }
    --1.3.6.1.4.1.3052.17.1.7.26

wmsSIMStatus OBJECT-TYPE
    SYNTAX DisplayString
    MAX-ACCESS read-only
    STATUS current
    DESCRIPTION
        "WWireless modem SIM status"
    ::= { wirelessModemStatus 27 }
    --1.3.6.1.4.1.3052.17.1.7.27

wmsICCID OBJECT-TYPE
    SYNTAX DisplayString
    MAX-ACCESS read-only
    STATUS current
    DESCRIPTION
        "Wireless modem SIM ICCID"
    ::= { wirelessModemStatus 28 }
    --1.3.6.1.4.1.3052.17.1.7.28

wmsModemType OBJECT-TYPE
    SYNTAX DisplayString
    MAX-ACCESS read-only
    STATUS current
    DESCRIPTION
        "Wireless modem type"
    ::= { wirelessModemStatus 29 }
    --1.3.6.1.4.1.3052.17.1.7.29


--***************************************************************************************
--AC Power Monitor Section 1.8
--***************************************************************************************

acpmStatusTable OBJECT-TYPE
    SYNTAX SEQUENCE OF ACPMStatus
    MAX-ACCESS not-accessible
    STATUS current
    DESCRIPTION
        "AC power monitor status table"
    ::= { acPowerMonitorStatus 1 }
    --1.3.6.1.4.1.3052.17.1.8.1

acpmStatusEntry OBJECT-TYPE
    SYNTAX ACPMStatus
    MAX-ACCESS not-accessible
    STATUS current
    DESCRIPTION
        "AC power monitor status table entry"
    INDEX { acpmsIndex }
    ::= { acpmStatusTable 1 }
    --1.3.6.1.4.1.3052.17.1.8.1.1

acpmsIndex OBJECT-TYPE
    SYNTAX Integer32 (1..6)
    MAX-ACCESS read-only
    STATUS current
    DESCRIPTION
        "Index for AC power monitors"
    ::= { acpmStatusEntry 1 }
    --1.3.6.1.4.1.3052.17.1.8.1.1.1

acpmsName OBJECT-TYPE
    SYNTAX DisplayString
    MAX-ACCESS read-only
    STATUS current
    DESCRIPTION
        "Name for the AC power monitor device."
    ::= { acpmStatusEntry 2 }
    --1.3.6.1.4.1.3052.17.1.8.1.1.2

acpmsAvgVoltageValueStr OBJECT-TYPE
    SYNTAX DisplayString
    MAX-ACCESS read-only
    STATUS current
    DESCRIPTION
        "Average voltage, in volts. This is calculated using the formula
        (register * PT ratio * 0.1). This could be either the average of
        the phase voltages, or the sum of the phase voltages, depending
        on device configuration."
    ::= { acpmStatusEntry 3 }
    --1.3.6.1.4.1.3052.17.1.8.1.1.3

acpmsAvgVoltageMinStr OBJECT-TYPE
    SYNTAX DisplayString
    MAX-ACCESS read-only
    STATUS current
    DESCRIPTION
        "Minimum average voltage value since last reset, in volts."
    ::= { acpmStatusEntry 4 }
    --1.3.6.1.4.1.3052.17.1.8.1.1.4

acpmsAvgVoltageMaxStr OBJECT-TYPE
    SYNTAX DisplayString
    MAX-ACCESS read-only
    STATUS current
    DESCRIPTION
        "Maximum average voltage value since last reset, in volts."
    ::= { acpmStatusEntry 5 }
    --1.3.6.1.4.1.3052.17.1.8.1.1.5

acpmsAvgVoltageAvgStr OBJECT-TYPE
    SYNTAX DisplayString
    MAX-ACCESS read-only
    STATUS current
    DESCRIPTION
        "Average average voltage value since last reset, in volts.  This is
        the unit's average of its measurements of the average voltage
        reported by the AC power monitor device."
    ::= { acpmStatusEntry 6 }
    --1.3.6.1.4.1.3052.17.1.8.1.1.6

acpmsAvgVoltageInEventState OBJECT-TYPE
    SYNTAX DisplayString
    MAX-ACCESS read-only
    STATUS current
    DESCRIPTION
        "Event state of this AC power monitor voltage (Low, Normal, High, etc.)."
    ::= { acpmStatusEntry 7 }
    --1.3.6.1.4.1.3052.17.1.8.1.1.7

acpmsVoltagePhaseAValueStr OBJECT-TYPE
    SYNTAX DisplayString
    MAX-ACCESS read-only
    STATUS current
    DESCRIPTION
        "Phase A voltage, in volts. This is calculated using the formula
        (register * PT ratio * 0.1)."
    ::= { acpmStatusEntry 8 }
    --1.3.6.1.4.1.3052.17.1.8.1.1.8

acpmsVoltagePhaseBValueStr OBJECT-TYPE
    SYNTAX DisplayString
    MAX-ACCESS read-only
    STATUS current
    DESCRIPTION
        "Phase B voltage, in volts. This is calculated using the formula
        (register * PT ratio * 0.1)."
    ::= { acpmStatusEntry 9 }
    --1.3.6.1.4.1.3052.17.1.8.1.1.9

acpmsVoltagePhaseCValueStr OBJECT-TYPE
    SYNTAX DisplayString
    MAX-ACCESS read-only
    STATUS current
    DESCRIPTION
        "Phase C voltage, in volts. This is calculated using the formula
        (register * PT ratio * 0.1)."
    ::= { acpmStatusEntry 10 }
    --1.3.6.1.4.1.3052.17.1.8.1.1.10

acpmsAvgCurrentValueStr OBJECT-TYPE
    SYNTAX DisplayString
    MAX-ACCESS read-only
    STATUS current
    DESCRIPTION
        "Average current, in amps. This is calculated using the formula
        (register * CT ratio * 0.001). This could be either the average of
        the phase currents, or the sum of the phase currents, depending on
        device configuration."
    ::= { acpmStatusEntry 11 }
    --1.3.6.1.4.1.3052.17.1.8.1.1.11

acpmsAvgCurrentMinStr OBJECT-TYPE
    SYNTAX DisplayString
    MAX-ACCESS read-only
    STATUS current
    DESCRIPTION
        "Minimum average current value since last reset, in amps."
    ::= { acpmStatusEntry 12 }
    --1.3.6.1.4.1.3052.17.1.8.1.1.12

acpmsAvgCurrentMaxStr OBJECT-TYPE
    SYNTAX DisplayString
    MAX-ACCESS read-only
    STATUS current
    DESCRIPTION
        "Maximum average current value since last reset, in amps."
    ::= { acpmStatusEntry 13 }
    --1.3.6.1.4.1.3052.17.1.8.1.1.13

acpmsAvgCurrentAvgStr OBJECT-TYPE
    SYNTAX DisplayString
    MAX-ACCESS read-only
    STATUS current
    DESCRIPTION
        "Average average current value since last reset, in amps.  This is
        the unit's average of its measurements of the average current reported
        by the AC power monitor device."
    ::= { acpmStatusEntry 14 }
    --1.3.6.1.4.1.3052.17.1.8.1.1.14

acpmsAvgCurrentInEventState OBJECT-TYPE
    SYNTAX DisplayString
    MAX-ACCESS read-only
    STATUS current
    DESCRIPTION
        "Event state of this AC power monitor current (Low, Normal, High, etc.)."
    ::= { acpmStatusEntry 15 }
    --1.3.6.1.4.1.3052.17.1.8.1.1.15

acpmsCurrentPhaseAValueStr OBJECT-TYPE
    SYNTAX DisplayString
    MAX-ACCESS read-only
    STATUS current
    DESCRIPTION
        "Phase A current, in amps. This is calculated using the formula
        (register * CT ratio * 0.001)."
    ::= { acpmStatusEntry 16 }
    --1.3.6.1.4.1.3052.17.1.8.1.1.16

acpmsCurrentPhaseBValueStr OBJECT-TYPE
    SYNTAX DisplayString
    MAX-ACCESS read-only
    STATUS current
    DESCRIPTION
        "Phase B current, in amps. This is calculated using the formula
        (register * CT ratio * 0.001)."
    ::= { acpmStatusEntry 17 }
    --1.3.6.1.4.1.3052.17.1.8.1.1.17

acpmsCurrentPhaseCValueStr OBJECT-TYPE
    SYNTAX DisplayString
    MAX-ACCESS read-only
    STATUS current
    DESCRIPTION
        "Phase C current, in amps. This is calculated using the formula
        (register * CT ratio * 0.001)."
    ::= { acpmStatusEntry 18 }
    --1.3.6.1.4.1.3052.17.1.8.1.1.18

acpmsAvgFreqValueStr OBJECT-TYPE
    SYNTAX DisplayString
    MAX-ACCESS read-only
    STATUS current
    DESCRIPTION
        "Frequency, in hertz. On the YD2010, this is calculated using the
        formula (register * 0.00106813). On the WattsOn, this is calculated
        using the formula (register * 0.1)."
    ::= { acpmStatusEntry 19 }
    --1.3.6.1.4.1.3052.17.1.8.1.1.19

acpmsAvgFreqMinStr OBJECT-TYPE
    SYNTAX DisplayString
    MAX-ACCESS read-only
    STATUS current
    DESCRIPTION
        "Minimum frequency value since last reset, in hertz."
    ::= { acpmStatusEntry 20 }
    --1.3.6.1.4.1.3052.17.1.8.1.1.20

acpmsAvgFreqMaxStr OBJECT-TYPE
    SYNTAX DisplayString
    MAX-ACCESS read-only
    STATUS current
    DESCRIPTION
        "Maximum frequency value since last reset, in hertz."
    ::= { acpmStatusEntry 21 }
    --1.3.6.1.4.1.3052.17.1.8.1.1.21

acpmsAvgFreqAvgStr OBJECT-TYPE
    SYNTAX DisplayString
    MAX-ACCESS read-only
    STATUS current
    DESCRIPTION
        "Average frequency value since last reset, in hertz.  This is the
        unit's average of its measurements of the average frequency reported
        by the AC power monitor device."
    ::= { acpmStatusEntry 22 }
    --1.3.6.1.4.1.3052.17.1.8.1.1.22

acpmsAvgFreqInEventState OBJECT-TYPE
    SYNTAX DisplayString
    MAX-ACCESS read-only
    STATUS current
    DESCRIPTION
        "Event state of this AC power monitor frequency (Low, Normal, High, etc.)."
    ::= { acpmStatusEntry 23 }
    --1.3.6.1.4.1.3052.17.1.8.1.1.23

acpmsTRPValueStr OBJECT-TYPE
    SYNTAX DisplayString
    MAX-ACCESS read-only
    STATUS current
    DESCRIPTION
        "Total real power, in watts. On the YD2010, this is calculated using
        the formula (register * PT ratio * CT ratio * Urg * 0.4), where Urg is
        the voltage range taken from register 0x30A. On the WattsOn models,
        this is calculated using the formula (register * PT * CT)."
    ::= { acpmStatusEntry 24 }
    --1.3.6.1.4.1.3052.17.1.8.1.1.24

acpmsTRPMinStr OBJECT-TYPE
    SYNTAX DisplayString
    MAX-ACCESS read-only
    STATUS current
    DESCRIPTION
        "Minimum total real power value since last reset, in watts."
    ::= { acpmStatusEntry 25 }
    --1.3.6.1.4.1.3052.17.1.8.1.1.25

acpmsTRPMaxStr OBJECT-TYPE
    SYNTAX DisplayString
    MAX-ACCESS read-only
    STATUS current
    DESCRIPTION
        "Maximum total real power value since last reset, in watts."
    ::= { acpmStatusEntry 26 }
    --1.3.6.1.4.1.3052.17.1.8.1.1.26

acpmsTRPAvgStr OBJECT-TYPE
    SYNTAX DisplayString
    MAX-ACCESS read-only
    STATUS current
    DESCRIPTION
        "Average total real power value since last reset, in watts.  This is
        the unit's average of its measurements of the average total real power
        reported by the AC power monitor device."
    ::= { acpmStatusEntry 27 }
    --1.3.6.1.4.1.3052.17.1.8.1.1.27

acpmsTRPInEventState OBJECT-TYPE
    SYNTAX DisplayString
    MAX-ACCESS read-only
    STATUS current
    DESCRIPTION
        "Event state of this AC power monitor total real power (Low, Normal,
        High, etc.)."
    ::= { acpmStatusEntry 28 }
    --1.3.6.1.4.1.3052.17.1.8.1.1.28

acpmsRPPhaseAValueStr OBJECT-TYPE
    SYNTAX DisplayString
    MAX-ACCESS read-only
    STATUS current
    DESCRIPTION
        "Phase A real power, in watts. On the YD2010, this is calculated using
        the formula (register * PT ratio * CT ratio * Urg * 0.4), where Urg is
        the voltage range taken from register 0x30A. On the WattsOn, this is
        calculated using the formula (register * PT * CT)."
    ::= { acpmStatusEntry 29 }
    --1.3.6.1.4.1.3052.17.1.8.1.1.29

acpmsRPPhaseBValueStr OBJECT-TYPE
    SYNTAX DisplayString
    MAX-ACCESS read-only
    STATUS current
    DESCRIPTION
        "Phase B real power, in watts. On the YD2010, this is calculated using
        the formula (register * PT ratio * CT ratio * Urg * 0.4), where Urg is
        the voltage range taken from register 0x30A. On the WattsOn, this is
        calculated using the formula (register * PT * CT)."
    ::= { acpmStatusEntry 30 }
    --1.3.6.1.4.1.3052.17.1.8.1.1.30

acpmsRPPhaseCValueStr OBJECT-TYPE
    SYNTAX DisplayString
    MAX-ACCESS read-only
    STATUS current
    DESCRIPTION
        "Phase C real power, in watts. On the YD2010, this is calculated using
        the formula (register * PT ratio * CT ratio * Urg * 0.4), where Urg is
        the voltage range taken from register 0x30A. On the WattsOn, this is
        calculated using the formula (register * PT * CT)."
    ::= { acpmStatusEntry 31 }
    --1.3.6.1.4.1.3052.17.1.8.1.1.31

acpmsCombined OBJECT-TYPE
    SYNTAX DisplayString
    MAX-ACCESS read-only
    STATUS current
    DESCRIPTION
        "Combined status string intended to be parsed by NMS:
        name`deviceState`deviceStateColorCode`voltage`current`frequency`power~voltageEventState`voltageColorCode`currentEventState`currentColorCode`frequencyEventState`frequencyColorCode`powerEventState`powerColorCode"
    ::= { acpmStatusEntry 32 }
    --1.3.6.1.4.1.3052.17.1.8.1.1.32

acpmsTPFValueStr OBJECT-TYPE
    SYNTAX DisplayString
    MAX-ACCESS read-only
    STATUS current
    DESCRIPTION
        "Total power factor."
    ::= { acpmStatusEntry 33 }
    --1.3.6.1.4.1.3052.17.1.8.1.1.33

acpmsTPFMinStr OBJECT-TYPE
    SYNTAX DisplayString
    MAX-ACCESS read-only
    STATUS current
    DESCRIPTION
        "Total power factor minimum value since last reset."
    ::= { acpmStatusEntry 34 }
    --1.3.6.1.4.1.3052.17.1.8.1.1.34

acpmsTPFMaxStr OBJECT-TYPE
    SYNTAX DisplayString
    MAX-ACCESS read-only
    STATUS current
    DESCRIPTION
        "Total power factor maximum value since last reset."
    ::= { acpmStatusEntry 35 }
    --1.3.6.1.4.1.3052.17.1.8.1.1.35

acpmsTPFAvgStr OBJECT-TYPE
    SYNTAX DisplayString
    MAX-ACCESS read-only
    STATUS current
    DESCRIPTION
        "Total power factor average value since last reset."
    ::= { acpmStatusEntry 36 }
    --1.3.6.1.4.1.3052.17.1.8.1.1.36

acpmsTPFInEventState OBJECT-TYPE
    SYNTAX DisplayString
    MAX-ACCESS read-only
    STATUS current
    DESCRIPTION
        "Total power factor event state."
    ::= { acpmStatusEntry 37 }
    --1.3.6.1.4.1.3052.17.1.8.1.1.37

acpmsPFPhaseAValueStr OBJECT-TYPE
    SYNTAX DisplayString
    MAX-ACCESS read-only
    STATUS current
    DESCRIPTION
        "Phase A power factor."
    ::= { acpmStatusEntry 38 }
    --1.3.6.1.4.1.3052.17.1.8.1.1.38

acpmsPFPhaseBValueStr OBJECT-TYPE
    SYNTAX DisplayString
    MAX-ACCESS read-only
    STATUS current
    DESCRIPTION
        "Phase B power factor."
    ::= { acpmStatusEntry 39 }
    --1.3.6.1.4.1.3052.17.1.8.1.1.39

acpmsPFPhaseCValueStr OBJECT-TYPE
    SYNTAX DisplayString
    MAX-ACCESS read-only
    STATUS current
    DESCRIPTION
        "Phase C power factor."
    ::= { acpmStatusEntry 40 }
    --1.3.6.1.4.1.3052.17.1.8.1.1.40

acpmsTRcPValueStr OBJECT-TYPE
    SYNTAX DisplayString
    MAX-ACCESS read-only
    STATUS current
    DESCRIPTION
        "Total reactive power, in VAR."
    ::= { acpmStatusEntry 41 }
    --1.3.6.1.4.1.3052.17.1.8.1.1.41

acpmsTRcPMinStr OBJECT-TYPE
    SYNTAX DisplayString
    MAX-ACCESS read-only
    STATUS current
    DESCRIPTION
        "Total reactive power minimum value since last reset, in VAR."
    ::= { acpmStatusEntry 42 }
    --1.3.6.1.4.1.3052.17.1.8.1.1.42

acpmsTRcPMaxStr OBJECT-TYPE
    SYNTAX DisplayString
    MAX-ACCESS read-only
    STATUS current
    DESCRIPTION
        "Total reactive power maximum value since last reset, in VAR."
    ::= { acpmStatusEntry 43 }
    --1.3.6.1.4.1.3052.17.1.8.1.1.43

acpmsTRcPAvgStr OBJECT-TYPE
    SYNTAX DisplayString
    MAX-ACCESS read-only
    STATUS current
    DESCRIPTION
        "Total reactive power average value since last reset, in VAR."
    ::= { acpmStatusEntry 44 }
    --1.3.6.1.4.1.3052.17.1.8.1.1.44

acpmsRcPPhaseAValueStr OBJECT-TYPE
    SYNTAX DisplayString
    MAX-ACCESS read-only
    STATUS current
    DESCRIPTION
        "Phase A reactive power, in VAR."
    ::= { acpmStatusEntry 45 }
    --1.3.6.1.4.1.3052.17.1.8.1.1.45

acpmsRcPPhaseBValueStr OBJECT-TYPE
    SYNTAX DisplayString
    MAX-ACCESS read-only
    STATUS current
    DESCRIPTION
        "Phase B reactive power, in VAR."
    ::= { acpmStatusEntry 46 }
    --1.3.6.1.4.1.3052.17.1.8.1.1.46

acpmsRcPPhaseCValueStr OBJECT-TYPE
    SYNTAX DisplayString
    MAX-ACCESS read-only
    STATUS current
    DESCRIPTION
        "Phase C reactive power, in VAR."
    ::= { acpmStatusEntry 47 }
    --1.3.6.1.4.1.3052.17.1.8.1.1.47

acpmsTAPValueStr OBJECT-TYPE
    SYNTAX DisplayString
    MAX-ACCESS read-only
    STATUS current
    DESCRIPTION
        "Total apparent power, in VA."
    ::= { acpmStatusEntry 48 }
    --1.3.6.1.4.1.3052.17.1.8.1.1.48

acpmsTAPMinStr OBJECT-TYPE
    SYNTAX DisplayString
    MAX-ACCESS read-only
    STATUS current
    DESCRIPTION
        "Total apparent power minimum value since last reset, in VA."
    ::= { acpmStatusEntry 49 }
    --1.3.6.1.4.1.3052.17.1.8.1.1.49

acpmsTAPMaxStr OBJECT-TYPE
    SYNTAX DisplayString
    MAX-ACCESS read-only
    STATUS current
    DESCRIPTION
        "Total apparent power maximum value since last reset, in VA."
    ::= { acpmStatusEntry 50 }
    --1.3.6.1.4.1.3052.17.1.8.1.1.50

acpmsTAPAvgStr OBJECT-TYPE
    SYNTAX DisplayString
    MAX-ACCESS read-only
    STATUS current
    DESCRIPTION
        "Total apparent power average value since last reset, in VA."
    ::= { acpmStatusEntry 51 }
    --1.3.6.1.4.1.3052.17.1.8.1.1.51

acpmsAPPhaseAValueStr OBJECT-TYPE
    SYNTAX DisplayString
    MAX-ACCESS read-only
    STATUS current
    DESCRIPTION
        "Phase A apparent power, in VA."
    ::= { acpmStatusEntry 52 }
    --1.3.6.1.4.1.3052.17.1.8.1.1.52

acpmsAPPhaseBValueStr OBJECT-TYPE
    SYNTAX DisplayString
    MAX-ACCESS read-only
    STATUS current
    DESCRIPTION
        "Phase B apparent power, in VA."
    ::= { acpmStatusEntry 53 }
    --1.3.6.1.4.1.3052.17.1.8.1.1.53

acpmsAPPhaseCValueStr OBJECT-TYPE
    SYNTAX DisplayString
    MAX-ACCESS read-only
    STATUS current
    DESCRIPTION
        "Phase C apparent power, in VA."
    ::= { acpmStatusEntry 54 }
    --1.3.6.1.4.1.3052.17.1.8.1.1.54

acpmsTotalEnergyWh OBJECT-TYPE
    SYNTAX Integer32
    MAX-ACCESS read-only
    STATUS current
    DESCRIPTION
        "Total energy, in Wh."
    ::= { acpmStatusEntry 55 }
    --1.3.6.1.4.1.3052.17.1.8.1.1.55

acpmsTotalEnergyVAR OBJECT-TYPE
    SYNTAX Integer32
    MAX-ACCESS read-only
    STATUS current
    DESCRIPTION
        "Total reactive energy, in VAR."
    ::= { acpmStatusEntry 56 }
    --1.3.6.1.4.1.3052.17.1.8.1.1.56

acpmsTotalEnergyVA OBJECT-TYPE
    SYNTAX Integer32
    MAX-ACCESS read-only
    STATUS current
    DESCRIPTION
        "Total apparent energy, in VA."
    ::= { acpmStatusEntry 57 }
    --1.3.6.1.4.1.3052.17.1.8.1.1.57


--***************************************************************************************
--Battery Monitor Status Section 1.10
--***************************************************************************************

bmStatusTable OBJECT-TYPE
    SYNTAX SEQUENCE OF BMStatus
    MAX-ACCESS not-accessible
    STATUS current
    DESCRIPTION
        "Battery monitor status table."
    ::= { batteryMonitorStatus 1 }
    --1.3.6.1.4.1.3052.17.1.10.1

bmStatusEntry OBJECT-TYPE
    SYNTAX BMStatus
    MAX-ACCESS not-accessible
    STATUS current
    DESCRIPTION
        "Battery monitor status table entry."
    INDEX { bmsIndex }
    ::= { bmStatusTable 1 }
    --1.3.6.1.4.1.3052.17.1.10.1.1

bmsIndex OBJECT-TYPE
    SYNTAX Integer32 (1..9)
    MAX-ACCESS read-only
    STATUS current
    DESCRIPTION
        "Index for battery monitors."
    ::= { bmStatusEntry 1 }
    --1.3.6.1.4.1.3052.17.1.10.1.1.1

bmsEnable OBJECT-TYPE
    SYNTAX DisplayString
    MAX-ACCESS read-only
    STATUS current
    DESCRIPTION
        "ON/OFF enable for this battery monitor."
    ::= { bmStatusEntry 2 }
    --1.3.6.1.4.1.3052.17.1.10.1.1.2

bmsName OBJECT-TYPE
    SYNTAX DisplayString
    MAX-ACCESS read-only
    STATUS current
    DESCRIPTION
        "Name for this battery monitor."
    ::= { bmStatusEntry 3 }
    --1.3.6.1.4.1.3052.17.1.10.1.1.3

bmsState OBJECT-TYPE
    SYNTAX DisplayString
    MAX-ACCESS read-only
    STATUS current
    DESCRIPTION
        "The connected state of the battery monitor.  If you unplug the carrier
        then all three of its battery monitor states will reflect the same
        state change."
    ::= { bmStatusEntry 4 }
    --1.3.6.1.4.1.3052.17.1.10.1.1.4

bmsStringState OBJECT-TYPE
    SYNTAX DisplayString
    MAX-ACCESS read-only
    STATUS current
    DESCRIPTION
        "State of the string monitored by its battery monitor."
    ::= { bmStatusEntry 5 }
    --1.3.6.1.4.1.3052.17.1.10.1.1.5

bmsTempValue OBJECT-TYPE
    SYNTAX DisplayString
    MAX-ACCESS read-only
    STATUS current
    DESCRIPTION
        "Average jar temperature value in C or F, depending on scale setting.
        Displayed as a floating point value.  -999.0 means this is unknown."
    ::= { bmStatusEntry 6 }
    --1.3.6.1.4.1.3052.17.1.10.1.1.6

bmsTempValueStr OBJECT-TYPE
    SYNTAX DisplayString
    MAX-ACCESS read-only
    STATUS current
    DESCRIPTION
        "Average jar temperature with appropriate scale appended. Displayed
        as a floating point value. -999.0 means this is unknown."
    ::= { bmStatusEntry 7 }
    --1.3.6.1.4.1.3052.17.1.10.1.1.7

bmsTempEvent OBJECT-TYPE
    SYNTAX DisplayString
    MAX-ACCESS read-only
    STATUS current
    DESCRIPTION
        "Event state of this battery monitor average jar temperature (Low,
        Normal, High)."
    ::= { bmStatusEntry 8 }
    --1.3.6.1.4.1.3052.17.1.10.1.1.8

bmsDiffTempValue OBJECT-TYPE
    SYNTAX Integer32
    MAX-ACCESS read-only
    STATUS current
    DESCRIPTION
        "Differential temperature in C or F, depending on scale setting.
        -999 means this is unknown."
    ::= { bmStatusEntry 9 }
    --1.3.6.1.4.1.3052.17.1.10.1.1.9

bmsDiffTempValueStr OBJECT-TYPE
    SYNTAX DisplayString
    MAX-ACCESS read-only
    STATUS current
    DESCRIPTION
        "Differential temperature with appropriate scale (C or F) appended.
        -999 means this is unknown."
    ::= { bmStatusEntry 10 }
    --1.3.6.1.4.1.3052.17.1.10.1.1.10

bmsDiffTempEvent OBJECT-TYPE
    SYNTAX DisplayString
    MAX-ACCESS read-only
    STATUS current
    DESCRIPTION
        "Event state of this battery monitor differential temperature
        (Very High, High, Normal)."
    ::= { bmStatusEntry 11 }
    --1.3.6.1.4.1.3052.17.1.10.1.1.11

bmsVoltageValue OBJECT-TYPE
    SYNTAX DisplayString
    MAX-ACCESS read-only
    STATUS current
    DESCRIPTION
        "Total battery voltage on the string, in volts.  Displayed as a
        floating point value in format X.X.  -999.0 means this is unknown."
    ::= { bmStatusEntry 12 }
    --1.3.6.1.4.1.3052.17.1.10.1.1.12

bmsVoltageEvent OBJECT-TYPE
    SYNTAX DisplayString
    MAX-ACCESS read-only
    STATUS current
    DESCRIPTION
        "Event state of this battery monitor string voltage (Low, Normal, High,
        etc.)."
    ::= { bmStatusEntry 13 }
    --1.3.6.1.4.1.3052.17.1.10.1.1.13

bmsDiffVoltValue OBJECT-TYPE
    SYNTAX DisplayString
    MAX-ACCESS read-only
    STATUS current
    DESCRIPTION
        "Differential voltage in volts.  Displayed as a floating point value
        in format X.X.  -999.0 means this is unknown."
    ::= { bmStatusEntry 14 }
    --1.3.6.1.4.1.3052.17.1.10.1.1.14

bmsDiffVoltEvent OBJECT-TYPE
    SYNTAX DisplayString
    MAX-ACCESS read-only
    STATUS current
    DESCRIPTION
        "Event state of this battery monitor differential voltage (Very High,
        High, Normal.)"
    ::= { bmStatusEntry 15 }
    --1.3.6.1.4.1.3052.17.1.10.1.1.15

bmsCurrentValue OBJECT-TYPE
    SYNTAX DisplayString
    MAX-ACCESS read-only
    STATUS current
    DESCRIPTION
        "Current flow on the string, in amperes.  Displayed as a floating point
        value in format X.X. A positive value means the battery string is
        charging, and a negative value means the battery string is discharging.
        -999.0 means this is unknown."
    ::= { bmStatusEntry 16 }
    --1.3.6.1.4.1.3052.17.1.10.1.1.16

bmsChargingCurrentEvent OBJECT-TYPE
    SYNTAX DisplayString
    MAX-ACCESS read-only
    STATUS current
    DESCRIPTION
        "Event state of this battery monitor charging current (Low, Normal,
        High, etc.)."
    ::= { bmStatusEntry 17 }
    --1.3.6.1.4.1.3052.17.1.10.1.1.17

bmsDischargingCurrentEvent OBJECT-TYPE
    SYNTAX DisplayString
    MAX-ACCESS read-only
    STATUS current
    DESCRIPTION
        "Event state of this battery monitor discharging current (Low, Normal,
        High, etc.)."
    ::= { bmStatusEntry 18 }
    --1.3.6.1.4.1.3052.17.1.10.1.1.18

bmsChargeLevelValue OBJECT-TYPE
    SYNTAX DisplayString
    MAX-ACCESS read-only
    STATUS current
    DESCRIPTION
        "Charge level of the battery string."
    ::= { bmStatusEntry 19 }
    --1.3.6.1.4.1.3052.17.1.10.1.1.19

bmsChargeLevelEvent OBJECT-TYPE
    SYNTAX DisplayString
    MAX-ACCESS read-only
    STATUS current
    DESCRIPTION
        "Event state of this battery monitor charge level (Very Low, Low,
        Normal)."
    ::= { bmStatusEntry 20 }
    --1.3.6.1.4.1.3052.17.1.10.1.1.20

bmsJarHealthValue OBJECT-TYPE
    SYNTAX DisplayString
    MAX-ACCESS read-only
    STATUS current
    DESCRIPTION
        "Jar health of the battery string."
    ::= { bmStatusEntry 21 }
    --1.3.6.1.4.1.3052.17.1.10.1.1.21

bmsJarHealthEvent OBJECT-TYPE
    SYNTAX DisplayString
    MAX-ACCESS read-only
    STATUS current
    DESCRIPTION
        "Event state of this battery monitor jar health (Very Low, Low,
        Normal)."
    ::= { bmStatusEntry 22 }
    --1.3.6.1.4.1.3052.17.1.10.1.1.22

bmsCombined OBJECT-TYPE
    SYNTAX DisplayString
    MAX-ACCESS read-only
    STATUS current
    DESCRIPTION
        "Combined status string intended to be parsed by NMS:
        name`deviceState`deviceStateColorCode`stringState`charge`voltage`temp`health~chargeEventState`chargeColorCode`voltageEventState`voltageColorCode`tempEventState`tempColorCode`healthEventState`healthColorCode`numActiveEvents"
    ::= { bmStatusEntry 23 }
    --1.3.6.1.4.1.3052.17.1.10.1.1.23


bmsJarStatusTable OBJECT-TYPE
    SYNTAX SEQUENCE OF BMJarStatus
    MAX-ACCESS not-accessible
    STATUS current
    DESCRIPTION
        "This table organizes per-jar attributes of a battery monitor:
        1. voltage
        2. temperature."
    ::= { batteryMonitorStatus 2 }
    --1.3.6.1.4.1.3052.17.1.10.2

bmJarStatusEntry OBJECT-TYPE
    SYNTAX BMJarStatus
    MAX-ACCESS not-accessible
    STATUS current
    DESCRIPTION
        "Entry for battery monitor jar status table.  Note this table uses
        2 SNMP indexes: the first for which battery monitor and the second for
        which jar."
    INDEX { bmjsIndexBM, bmjsIndexJar }
    ::= { bmsJarStatusTable 1 }
    --1.3.6.1.4.1.3052.17.1.10.2.1

bmjsIndexBM OBJECT-TYPE
    SYNTAX Integer32 (1..9)
    MAX-ACCESS read-only
    STATUS current
    DESCRIPTION
        "The part of the index that refers to which battery monitor."
    ::= { bmJarStatusEntry 1 }
    --1.3.6.1.4.1.3052.17.1.10.2.1.1

bmjsIndexJar OBJECT-TYPE
    SYNTAX Integer32 (1..12)
    MAX-ACCESS read-only
    STATUS current
    DESCRIPTION
        "The part of the index that refers to which jar."
    ::= { bmJarStatusEntry 2 }
    --1.3.6.1.4.1.3052.17.1.10.2.1.2

bmjsVoltageValue OBJECT-TYPE
    SYNTAX DisplayString
    MAX-ACCESS read-only
    STATUS current
    DESCRIPTION
        "Voltage of individual battery cell.  This is a floating point value
        in format X.X.  -999.0 means this is unknown."
    ::= { bmJarStatusEntry 3 }
    --1.3.6.1.4.1.3052.17.1.10.2.1.3

bmjsTempValue OBJECT-TYPE
    SYNTAX DisplayString
    MAX-ACCESS read-only
    STATUS current
    DESCRIPTION
        "Temperature of individual battery jar.  This is a floating point
        value.  -999.0 means unknown."
    ::= { bmJarStatusEntry 4 }
    --1.3.6.1.4.1.3052.17.1.10.2.1.4

bmjsAdmittanceValue OBJECT-TYPE
    SYNTAX Integer32
    MAX-ACCESS read-only
    STATUS current
    DESCRIPTION
        "Cell admittance of individual jar. This is an integer value.
        -999 means unknown."
    ::= { bmJarStatusEntry 5 }
    --1.3.6.1.4.1.3052.17.1.10.2.1.5

bmjsAdmittanceChangeValue OBJECT-TYPE
    SYNTAX Integer32
    MAX-ACCESS read-only
    STATUS current
    DESCRIPTION
        "Percent change of cell admittance of individual jar. This is an
        integer value."
    ::= { bmJarStatusEntry 6 }
    --1.3.6.1.4.1.3052.17.1.10.2.1.6


--***************************************************************************************
--EventSensor Basics Section    2.1
--***************************************************************************************

esNumberEventSensors OBJECT-TYPE
    SYNTAX Integer32
    MAX-ACCESS read-only
    STATUS current
    DESCRIPTION
        "The number of EventSensors recognized by the unit,
        including the internal EventSensor.
        Range: 1-17"
    ::= { eventSensorBasics 1 }
    --1.3.6.1.4.1.3052.17.2.1.1

esTable OBJECT-TYPE
    SYNTAX SEQUENCE OF ESExist
    MAX-ACCESS not-accessible
    STATUS current
    DESCRIPTION
        "The table of what EventSensors are attached to the unit,
        including the internal EventSensor"
    ::= { eventSensorBasics 2 }
    --1.3.6.1.4.1.3052.17.2.1.2

esEntry OBJECT-TYPE
    SYNTAX ESExist
    MAX-ACCESS not-accessible
    STATUS current
    DESCRIPTION
        "Table entry for EventSensor table"
    INDEX { esIndex }
    ::= { esTable 1 }
    --1.3.6.1.4.1.3052.17.2.1.2.1

esIndex OBJECT-TYPE
    SYNTAX Integer32 (1..200)
    MAX-ACCESS read-only
    STATUS current
    DESCRIPTION
        "This number refers to an EventSensor; it has the
        same meaning as the esIndexES object (see above),
        except that this object is used only within the
        esTable branch.

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndex=2
        will now refer to that particular EventSensor.
        "
    ::= { esEntry 1 }
    --1.3.6.1.4.1.3052.17.2.1.2.1.1

esName  OBJECT-TYPE
    SYNTAX DisplayString
    MAX-ACCESS read-only
    STATUS current
    DESCRIPTION
        "The name of the EventSensor"
    ::= { esEntry 2 }
    --1.3.6.1.4.1.3052.17.2.1.2.1.2

esID    OBJECT-TYPE
    SYNTAX DisplayString
    MAX-ACCESS read-only
    STATUS current
    DESCRIPTION
        "The factory-assigned ID of the EventSensor"
    ::= { esEntry 3 }
    --1.3.6.1.4.1.3052.17.2.1.2.1.3

esNumberTempSensors OBJECT-TYPE
    SYNTAX Integer32
    MAX-ACCESS read-only
    STATUS current
    DESCRIPTION
        "The number of temperature sensors on the EventSensor"
    ::= { esEntry 4 }
    --1.3.6.1.4.1.3052.17.2.1.2.1.4

esTempReportingMode OBJECT-TYPE
    SYNTAX DisplayString
    MAX-ACCESS read-only
    STATUS current
    DESCRIPTION
        "Description of how temperature values should
        be interpreted."
    ::= { esEntry 5 }
    --1.3.6.1.4.1.3052.17.2.1.2.1.5

esNumberCCs OBJECT-TYPE
    SYNTAX Integer32
    MAX-ACCESS read-only
    STATUS current
    DESCRIPTION
        "The number of contact closures on the EventSensor."
    ::= { esEntry 6 }
    --1.3.6.1.4.1.3052.17.2.1.2.1.6

esCCReportingMode OBJECT-TYPE
    SYNTAX DisplayString
    MAX-ACCESS read-only
    STATUS current
    DESCRIPTION
        "Description of how CC values should be interpreted."
    ::= { esEntry 7 }
    --1.3.6.1.4.1.3052.17.2.1.2.1.7

esNumberHumidSensors OBJECT-TYPE
    SYNTAX Integer32
    MAX-ACCESS read-only
    STATUS current
    DESCRIPTION
        "The number of humidity sensors on the EventSensor."
    ::= { esEntry 8 }
    --1.3.6.1.4.1.3052.17.2.1.2.1.8

esHumidReportingMode OBJECT-TYPE
    SYNTAX DisplayString
    MAX-ACCESS read-only
    STATUS current
    DESCRIPTION
        "Description of how humidity sensor values should be
        interpreted."
    ::= { esEntry 9 }
    --1.3.6.1.4.1.3052.17.2.1.2.1.9

esNumberNoiseSensors OBJECT-TYPE
    SYNTAX Integer32
    MAX-ACCESS read-only
    STATUS current
    DESCRIPTION
        "The number of noise sensors on the EventSensor."
    ::= { esEntry 10 }
    --1.3.6.1.4.1.3052.17.2.1.2.1.10

esNoiseReportingMode OBJECT-TYPE
    SYNTAX DisplayString
    MAX-ACCESS read-only
    STATUS current
    DESCRIPTION
        "Description of how noise sensor values should be
        interpreted."
    ::= { esEntry 11 }
    --1.3.6.1.4.1.3052.17.2.1.2.1.11

esNumberAirflowSensors OBJECT-TYPE
    SYNTAX Integer32
    MAX-ACCESS read-only
    STATUS current
    DESCRIPTION
        "The number of airflow sensors on the EventSensor."
    ::= { esEntry 12 }
    --1.3.6.1.4.1.3052.17.2.1.2.1.12

esAirflowReportingMode OBJECT-TYPE
    SYNTAX DisplayString
    MAX-ACCESS read-only
    STATUS current
    DESCRIPTION
        "Description of how airflow sensor values should be
        interpreted."
    ::= { esEntry 13 }
    --1.3.6.1.4.1.3052.17.2.1.2.1.13

esNumberAnalog OBJECT-TYPE
    SYNTAX Integer32
    MAX-ACCESS read-only
    STATUS current
    DESCRIPTION
        "The number of analog inputs on the EventSensor."
    ::= { esEntry 14 }
    --1.3.6.1.4.1.3052.17.2.1.2.1.14

esAnalogReportingMode OBJECT-TYPE
    SYNTAX DisplayString
    MAX-ACCESS read-only
    STATUS current
    DESCRIPTION
        "Description of how analog input values should be
        interpreted."
    ::= { esEntry 15 }
    --1.3.6.1.4.1.3052.17.2.1.2.1.15

esNumberRelayOutputs OBJECT-TYPE
    SYNTAX Integer32
    MAX-ACCESS read-only
    STATUS current
    DESCRIPTION
        "The number of relay outputs on the EventSensor"
    ::= { esEntry 16 }
    --1.3.6.1.4.1.3052.17.2.1.2.1.16

esRelayReportingMode OBJECT-TYPE
    SYNTAX DisplayString
    MAX-ACCESS read-only
    STATUS current
    DESCRIPTION
        "Description of how relay output values
        should be interpreted."
    ::= { esEntry 17 }
    --1.3.6.1.4.1.3052.17.2.1.2.1.17

esTempCombinedStatus OBJECT-TYPE
    SYNTAX DisplayString
    MAX-ACCESS read-only
    STATUS current
    DESCRIPTION
        "Combined status string intended to be parsed by NMS:
        name`value`scale`eventState`eventColorCode"
    ::= { esEntry 18 }
    --1.3.6.1.4.1.3052.17.2.1.2.1.18

esCCCombinedStatusBlock1 OBJECT-TYPE
    SYNTAX DisplayString
    MAX-ACCESS read-only
    STATUS current
    DESCRIPTION
        "Combined status string intended to be parsed by NMS:
        numInBlock~name1`value1`eventColorCode1`alias1~name2`value2`eventColorCode2`alias2~...name8`value8`eventColorCode8`alias8"
    ::= { esEntry 19 }
    --1.3.6.1.4.1.3052.17.2.1.2.1.19

esCCCombinedStatusBlock2 OBJECT-TYPE
    SYNTAX DisplayString
    MAX-ACCESS read-only
    STATUS current
    DESCRIPTION
        "Combined status string intended to be parsed by NMS:
        numInBlock~name9`value9`eventColorCode9`alias9~name10`value10`eventColorCode10`alias10~...name16`value16`eventColorCode16`alias16"
    ::= { esEntry 20 }
    --1.3.6.1.4.1.3052.17.2.1.2.1.20

esCCCombinedStatusBlock3 OBJECT-TYPE
    SYNTAX DisplayString
    MAX-ACCESS read-only
    STATUS current
    DESCRIPTION
        "Combined status string intended to be parsed by NMS:
        numInBlock~name17`value17`eventColorCode17`alias17~name18`value18`eventColorCode18`alias18~...name24`value24`eventColorCode24`alias24"
    ::= { esEntry 21 }
    --1.3.6.1.4.1.3052.17.2.1.2.1.21

esCCCombinedStatusBlock4 OBJECT-TYPE
    SYNTAX DisplayString
    MAX-ACCESS read-only
    STATUS current
    DESCRIPTION
        "Combined status string intended to be parsed by NMS:
        numInBlock~name25`value25`eventColorCode25`alias25~name26`value26`eventColorCode26`alias26~...name32`value32`eventColorCode32`alias32"
    ::= { esEntry 22 }
    --1.3.6.1.4.1.3052.17.2.1.2.1.22

esCCCombinedStatusBlock5 OBJECT-TYPE
    SYNTAX DisplayString
    MAX-ACCESS read-only
    STATUS current
    DESCRIPTION
        "Combined status string intended to be parsed by NMS:
        numInBlock~name33`value33`eventColorCode33`alias33~name34`value34`eventColorCode34`alias35~...name40`value40`eventColorCode40`alias40"
    ::= { esEntry 23 }
    --1.3.6.1.4.1.3052.17.2.1.2.1.23

esCCCombinedStatusBlock6 OBJECT-TYPE
    SYNTAX DisplayString
    MAX-ACCESS read-only
    STATUS current
    DESCRIPTION
        "Combined status string intended to be parsed by NMS:
        numInBlock~name41`value41`eventColorCode41`alias41~name42`value42`eventColorCode42`alias43~...name48`value48`eventColorCode48`alias48"
    ::= { esEntry 24 }
    --1.3.6.1.4.1.3052.17.2.1.2.1.24

esCCCombinedStatusBlock7 OBJECT-TYPE
    SYNTAX DisplayString
    MAX-ACCESS read-only
    STATUS current
    DESCRIPTION
        "Combined status string intended to be parsed by NMS:
        numInBlock~name49`value49`eventColorCode49`alias49~name50`value50`eventColorCode50`alias50~...name56`value56`eventColorCode56`alias56"
    ::= { esEntry 25 }
    --1.3.6.1.4.1.3052.17.2.1.2.1.25

esCCCombinedStatusBlock8 OBJECT-TYPE
    SYNTAX DisplayString
    MAX-ACCESS read-only
    STATUS current
    DESCRIPTION
        "Combined status string intended to be parsed by NMS:
        numInBlock~name57`value57`eventColorCode57`alias57~name57`value57`eventColorCode564`alias57~...name64`value64`eventColorCode64`alias64"
    ::= { esEntry 26 }
    --1.3.6.1.4.1.3052.17.2.1.2.1.26

esHumidCombinedStatus OBJECT-TYPE
    SYNTAX DisplayString
    MAX-ACCESS read-only
    STATUS current
    DESCRIPTION
        "Combined status string intended to be parsed by NMS:
        name`value`eventState`eventColorCode"
    ::= { esEntry 27 }
    --1.3.6.1.4.1.3052.17.2.1.2.1.27

esAnalogCombinedStatusBlock1 OBJECT-TYPE
    SYNTAX DisplayString
    MAX-ACCESS read-only
    STATUS current
    DESCRIPTION
        "Combined status string intended to be parsed by NMS:
        numInBlock~name1`value1`units1`eventState`eventColorCode1~name2`value2`units2`eventState`eventColorCode2~..."
    ::= { esEntry 28 }
    --1.3.6.1.4.1.3052.17.2.1.2.1.28

esAnalogCombinedStatusBlock2 OBJECT-TYPE
    SYNTAX DisplayString
    MAX-ACCESS read-only
    STATUS current
    DESCRIPTION
        "Combined status string intended to be parsed by NMS:
        numInBlock~name9`value9`units9`eventState9`eventColorCode9~..."
    ::= { esEntry 29 }
    --1.3.6.1.4.1.3052.17.2.1.2.1.29

esAnalogCombinedStatusBlock3 OBJECT-TYPE
    SYNTAX DisplayString
    MAX-ACCESS read-only
    STATUS current
    DESCRIPTION
        "Combined status string intended to be parsed by NMS:
        numInBlock~namex`valuex`unitsx`eventStatex`eventColorCodex~..."
    ::= { esEntry 30 }
    --1.3.6.1.4.1.3052.17.2.1.2.1.31

esAnalogCombinedStatusBlock4 OBJECT-TYPE
    SYNTAX DisplayString
    MAX-ACCESS read-only
    STATUS current
    DESCRIPTION
        "Combined status string intended to be parsed by NMS:
        numInBlock~namex`valuex`unitsx`eventStatex`eventColorCodex~..."
    ::= { esEntry 31 }
    --1.3.6.1.4.1.3052.17.2.1.2.1.31

esAnalogCombinedStatusBlock5 OBJECT-TYPE
    SYNTAX DisplayString
    MAX-ACCESS read-only
    STATUS current
    DESCRIPTION
        "Combined status string intended to be parsed by NMS:
        numInBlock~namex`valuex`unitsx`eventStatex`eventColorCodex~..."
    ::= { esEntry 32 }
    --1.3.6.1.4.1.3052.17.2.1.2.1.32

esAnalogCombinedStatusBlock6 OBJECT-TYPE
    SYNTAX DisplayString
    MAX-ACCESS read-only
    STATUS current
    DESCRIPTION
        "Combined status string intended to be parsed by NMS:
        numInBlock~namex`valuex`unitsx`eventStatex`eventColorCodex~..."
    ::= { esEntry 33 }
    --1.3.6.1.4.1.3052.17.2.1.2.1.33

esOutputCombinedStatusBlock1 OBJECT-TYPE
    SYNTAX DisplayString
    MAX-ACCESS read-only
    STATUS current
    DESCRIPTION
        "Combined status string intended to be parsed by NMS:
        numInBlock~namex`valuex`unitsx`eventStatex`eventColorCodex~..."
    ::= { esEntry 34 }
    --1.3.6.1.4.1.3052.17.2.1.2.1.34

esOutputCombinedStatusBlock2 OBJECT-TYPE
    SYNTAX DisplayString
    MAX-ACCESS read-only
    STATUS current
    DESCRIPTION
        "Combined status string intended to be parsed by NMS:
        numInBlock`namex`valuex`aliasx~namey`valuey`aliasy~...namez`valuez`aliasz"
    ::= { esEntry 35 }
    --1.3.6.1.4.1.3052.17.2.1.2.1.35

esNewSensors OBJECT-TYPE
    SYNTAX DisplayString
    MAX-ACCESS read-only
    STATUS current
    DESCRIPTION
        "String representing the number of new (attached but unconfigured) EventSensors"
    ::= { eventSensorBasics 3 }
    --1.3.6.1.4.1.3052.17.2.1.3


--***************************************************************************************
--EventSensor Point Config Section   2.2
--***************************************************************************************



esPointConfigTempTable OBJECT-TYPE
    SYNTAX SEQUENCE OF ESPointConfigTemp
    MAX-ACCESS not-accessible
    STATUS current
    DESCRIPTION
        "This table organizes 3 basic attributes of temperature
        sensor points.  A point is a particular sensor on an
        EventSensor.  The 3 point attributes organizes in this table
        are:
        1. the configuration item (e.g., enable, name, etc.)
        2. the eventsensor on which this point resides
        3. the point number (always 1 for temp sensors)

        Points are referenced by a point config index.  The point
        config index is a string of 2 numbers separated by periods.
        It contains all the information necessary for getting a
        piece of data off an event sensor within the context of this
        emperature point config table ; namely, which EventSensor,
        and which sensor (a.k.a. point) (always 1 for temperature
        sensors).
        "
    ::= { eventSensorPointConfig 1 }
    --1.3.6.1.4.1.3052.17.2.2.1

esPointConfigTempEntry OBJECT-TYPE
    SYNTAX ESPointConfigTemp
    MAX-ACCESS not-accessible
    STATUS current
    DESCRIPTION
        "Entry for EventSensor point config temperature table"
    INDEX { espcTempIndexES, espcTempIndexPoint }
    ::= { esPointConfigTempTable 1 }
    --1.3.6.1.4.1.3052.17.2.2.1.1

espcTempIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config temperature table; namely, which EventSensor,
        and which sensor (a.k.a. point).

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndexES=2
        will now refer to that particular EventSensor.
        "
    ::= { esPointConfigTempEntry 1 }
    --1.3.6.1.4.1.3052.17.2.2.1.1.1

espcTempIndexPoint OBJECT-TYPE
    SYNTAX Integer32 (1..64)
    MAX-ACCESS read-only
    STATUS current
    DESCRIPTION
        "The part of the point index that delineates which
        sensor on the EventSensor.

        So this combined with espcTempIndexES (which EventSensor)
        uniquely defines each point attached to a unit within the
        context of temperature point configuration."
    ::= { esPointConfigTempEntry 2 }
    --1.3.6.1.4.1.3052.17.2.2.1.1.2

espcTempEnable OBJECT-TYPE
    SYNTAX DisplayString
    MAX-ACCESS read-write
    STATUS current
    DESCRIPTION
        "ON/OFF enable this temperature sensor"
    ::= { esPointConfigTempEntry 3 }
    --1.3.6.1.4.1.3052.17.2.2.1.1.3

espcTempScale OBJECT-TYPE
    SYNTAX DisplayString
    MAX-ACCESS read-write
    STATUS current
    DESCRIPTION
        "Scale (C/F) for this temperature sensor"
    ::= { esPointConfigTempEntry 4 }
    --1.3.6.1.4.1.3052.17.2.2.1.1.4

espcTempDeadband OBJECT-TYPE
    SYNTAX DisplayString
    MAX-ACCESS read-write
    STATUS current
    DESCRIPTION
        "Deadband for this temperature sensor (in floating-point format)"
    ::= { esPointConfigTempEntry 5 }
    --1.3.6.1.4.1.3052.17.2.2.1.1.5

espcTempVHighTemp OBJECT-TYPE
    SYNTAX DisplayString
    MAX-ACCESS read-write
    STATUS current
    DESCRIPTION
        "Very high temperature event threshold for this temperature
        sensor (in floating-point format)"
    ::= { esPointConfigTempEntry 6 }
    --1.3.6.1.4.1.3052.17.2.2.1.1.6

espcTempVHighActions OBJECT-TYPE
    SYNTAX DisplayString
    MAX-ACCESS read-write
    STATUS current
    DESCRIPTION
        "Very high temperature event actions for this temperature
        sensor"
    ::= { esPointConfigTempEntry 7 }
    --1.3.6.1.4.1.3052.17.2.2.1.1.7

espcTempVHighTrapnum OBJECT-TYPE
    SYNTAX Integer32
    MAX-ACCESS read-write
    STATUS current
    DESCRIPTION
        "Very high temperature event trap number for this
        temperature sensor"
    ::= { esPointConfigTempEntry 8 }
    --1.3.6.1.4.1.3052.17.2.2.1.1.8

espcTempVHighClass OBJECT-TYPE
    SYNTAX DisplayString
    MAX-ACCESS read-write
    STATUS current
    DESCRIPTION
        "Very high temperature event class for this temperature
        sensor"
    ::= { esPointConfigTempEntry 9 }
    --1.3.6.1.4.1.3052.17.2.2.1.1.9

espcTempHighTemp OBJECT-TYPE
    SYNTAX DisplayString
    MAX-ACCESS read-write
    STATUS current
    DESCRIPTION
        "High temperature event threshold for this temperature
        sensor (in floating-point format)"
    ::= { esPointConfigTempEntry 10 }
    --1.3.6.1.4.1.3052.17.2.2.1.1.10

espcTempHighActions OBJECT-TYPE
    SYNTAX DisplayString
    MAX-ACCESS read-write
    STATUS current
    DESCRIPTION
        "High temperature event actions for this temperature sensor"
    ::= { esPointConfigTempEntry 11 }
    --1.3.6.1.4.1.3052.17.2.2.1.1.11

espcTempHighTrapnum OBJECT-TYPE
    SYNTAX Integer32
    MAX-ACCESS read-write
    STATUS current
    DESCRIPTION
        "High temperature event trap number for this temperature
        sensor"
    ::= { esPointConfigTempEntry 12 }
    --1.3.6.1.4.1.3052.17.2.2.1.1.12

espcTempHighClass OBJECT-TYPE
    SYNTAX DisplayString
    MAX-ACCESS read-write
    STATUS current
    DESCRIPTION
        "High temperature event class for this temperature sensor"
    ::= { esPointConfigTempEntry 13 }
    --1.3.6.1.4.1.3052.17.2.2.1.1.13

espcTempNormalActions OBJECT-TYPE
    SYNTAX DisplayString
    MAX-ACCESS read-write
    STATUS current
    DESCRIPTION
        "Return-to-normal event actions for this temperature sensor"
    ::= { esPointConfigTempEntry 14 }
    --1.3.6.1.4.1.3052.17.2.2.1.1.14

espcTempNormalTrapnum OBJECT-TYPE
    SYNTAX Integer32
    MAX-ACCESS read-write
    STATUS current
    DESCRIPTION
        "Return-to-normal event trap number for this temperature
        sensor"
    ::= { esPointConfigTempEntry 15 }
    --1.3.6.1.4.1.3052.17.2.2.1.1.15

espcTempNormalClass OBJECT-TYPE
    SYNTAX DisplayString
    MAX-ACCESS read-write
    STATUS current
    DESCRIPTION
        "Return-to-normal event class for this temperature sensor"
    ::= { esPointConfigTempEntry 16 }
    --1.3.6.1.4.1.3052.17.2.2.1.1.16

espcTempLowTemp OBJECT-TYPE
    SYNTAX DisplayString
    MAX-ACCESS read-write
    STATUS current
    DESCRIPTION
        "Low temperature event threshold for this temperature sensor
        (in floating-point format)"
    ::= { esPointConfigTempEntry 17 }
    --1.3.6.1.4.1.3052.17.2.2.1.1.17

espcTempLowActions OBJECT-TYPE
    SYNTAX DisplayString
    MAX-ACCESS read-write
    STATUS current
    DESCRIPTION
        "Low temperature event actions for this temperature sensor"
    ::= { esPointConfigTempEntry 18 }
    --1.3.6.1.4.1.3052.17.2.2.1.1.18

espcTempLowTrapnum OBJECT-TYPE
    SYNTAX Integer32
    MAX-ACCESS read-write
    STATUS current
    DESCRIPTION
        "Low temperature event trap number for this temperature
        sensor"
    ::= { esPointConfigTempEntry 19 }
    --1.3.6.1.4.1.3052.17.2.2.1.1.19

espcTempLowClass OBJECT-TYPE
    SYNTAX DisplayString
    MAX-ACCESS read-write
    STATUS current
    DESCRIPTION
        "Low temperature event class for this temperature sensor"
    ::= { esPointConfigTempEntry 20 }
    --1.3.6.1.4.1.3052.17.2.2.1.1.20

espcTempVLowTemp OBJECT-TYPE
    SYNTAX DisplayString
    MAX-ACCESS read-write
    STATUS current
    DESCRIPTION
        "Very Low temperature event threshold for this temperature
        sensor (in floating-point format)"
    ::= { esPointConfigTempEntry 21 }
    --1.3.6.1.4.1.3052.17.2.2.1.1.21

espcTempVLowActions OBJECT-TYPE
    SYNTAX DisplayString
    MAX-ACCESS read-write
    STATUS current
    DESCRIPTION
        "Very Low temperature event actions for this temperature
        sensor"
    ::= { esPointConfigTempEntry 22 }
    --1.3.6.1.4.1.3052.17.2.2.1.1.22

espcTempVLowTrapnum OBJECT-TYPE
    SYNTAX Integer32
    MAX-ACCESS read-write
    STATUS current
    DESCRIPTION
        "Very Low temperature event trap number for this temperature
        sensor"
    ::= { esPointConfigTempEntry 23 }
    --1.3.6.1.4.1.3052.17.2.2.1.1.23

espcTempVLowClass OBJECT-TYPE
    SYNTAX DisplayString
    MAX-ACCESS read-write
    STATUS current
    DESCRIPTION
        "Very Low temperature event class for this temperature sensor"
    ::= { esPointConfigTempEntry 24 }
    --1.3.6.1.4.1.3052.17.2.2.1.1.24





esPointConfigCCTable OBJECT-TYPE
    SYNTAX SEQUENCE OF ESPointConfigCC
    MAX-ACCESS not-accessible
    STATUS current
    DESCRIPTION
        "This table organizes 3 basic attributes of contact closure
        points.  A point is a particular sensor on an EventSensor.
        The 3 point attributes organizes in this table are:
        1. the configuration item (e.g., enable, name, etc.)
        2. the eventsensor on which this point resides
        3. the point number

        Points are referenced by a point config index.  The point
        config index is a string of 2 numbers separated by a period.
        It contains all the information necessary for getting a piece
        of data off an event sensor within the context of this
        contact closure point config table ; namely, which
        EventSensor and which sensor.
        "
    ::= { eventSensorPointConfig 2 }
    --1.3.6.1.4.1.3052.17.2.2.2

esPointConfigCCEntry OBJECT-TYPE
    SYNTAX ESPointConfigCC
    MAX-ACCESS not-accessible
    STATUS current
    DESCRIPTION
        "Entry for EventSensor point config contact closure table"
    INDEX { espcCCIndexES, espcCCIndexPoint }
    ::= { esPointConfigCCTable 1 }
    --1.3.6.1.4.1.3052.17.2.2.2.1

espcCCIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigCCEntry 1 }
    --1.3.6.1.4.1.3052.17.2.2.2.1.1

espcCCIndexPoint OBJECT-TYPE
    SYNTAX Integer32 (1..64)
    MAX-ACCESS read-only
    STATUS current
    DESCRIPTION
        "The part of the point index that delineates which
        sensor on the EventSensor.

        So this combined with espcCCIndexES (which EventSensor)
        uniquely defines each point attached to a unit within the
        context of contact closure point configuration."
    ::= { esPointConfigCCEntry 2 }
    --1.3.6.1.4.1.3052.17.2.2.2.1.2

espcCCEnable OBJECT-TYPE
    SYNTAX DisplayString
    MAX-ACCESS read-write
    STATUS current
    DESCRIPTION
        "ON/OFF enable for this contact closure"
    ::= { esPointConfigCCEntry 3 }
    --1.3.6.1.4.1.3052.17.2.2.2.1.3

espcCCName OBJECT-TYPE
    SYNTAX DisplayString
    MAX-ACCESS read-write
    STATUS current
    DESCRIPTION
        "Name for this contact closure"
    ::= { esPointConfigCCEntry 4 }
    --1.3.6.1.4.1.3052.17.2.2.2.1.4

espcCCEventState OBJECT-TYPE
    SYNTAX DisplayString
    MAX-ACCESS read-write
    STATUS current
    DESCRIPTION
        "Event state for this contact closure"
    ::= { esPointConfigCCEntry 5 }
    --1.3.6.1.4.1.3052.17.2.2.2.1.5

espcCCThreshold OBJECT-TYPE
    SYNTAX Integer32 (0..65535)
    MAX-ACCESS read-write
    STATUS current
    DESCRIPTION
        "Event threshold (seconds) for this contact closure"
    ::= { esPointConfigCCEntry 6 }
    --1.3.6.1.4.1.3052.17.2.2.2.1.6

espcCCEventActions OBJECT-TYPE
    SYNTAX DisplayString
    MAX-ACCESS read-write
    STATUS current
    DESCRIPTION
        "Event actions for this contact closure"
    ::= { esPointConfigCCEntry 7 }
    --1.3.6.1.4.1.3052.17.2.2.2.1.7

espcCCEventTrapnum OBJECT-TYPE
    SYNTAX Integer32
    MAX-ACCESS read-write
    STATUS current
    DESCRIPTION
        "Event trap number for this contact closure"
    ::= { esPointConfigCCEntry 8 }
    --1.3.6.1.4.1.3052.17.2.2.2.1.8

espcCCEventClass OBJECT-TYPE
    SYNTAX DisplayString
    MAX-ACCESS read-write
    STATUS current
    DESCRIPTION
        "Event class for this contact closure"
    ::= { esPointConfigCCEntry 9 }
    --1.3.6.1.4.1.3052.17.2.2.2.1.9

espcCCNormalActions OBJECT-TYPE
    SYNTAX DisplayString
    MAX-ACCESS read-write
    STATUS current
    DESCRIPTION
        "Return-to-normal actions for this contact closure"
    ::= { esPointConfigCCEntry 10 }
    --1.3.6.1.4.1.3052.17.2.2.2.1.10

espcCCNormalTrapnum OBJECT-TYPE
    SYNTAX Integer32
    MAX-ACCESS read-write
    STATUS current
    DESCRIPTION
        "Return-to-normal trap number for this contact closure"
    ::= { esPointConfigCCEntry 11 }
    --1.3.6.1.4.1.3052.17.2.2.2.1.11

espcCCNormalClass OBJECT-TYPE
    SYNTAX DisplayString
    MAX-ACCESS read-write
    STATUS current
    DESCRIPTION
        "Return-to-normal class for this contact closure"
    ::= { esPointConfigCCEntry 12 }
    --1.3.6.1.4.1.3052.17.2.2.2.1.12

espcCCAlarmAlias OBJECT-TYPE
    SYNTAX DisplayString
    MAX-ACCESS read-write
    STATUS current
    DESCRIPTION
        "Event alias for this contact closure"
    ::= { esPointConfigCCEntry 13 }
    --1.3.6.1.4.1.3052.17.2.2.2.1.13

espcCCNormalAlias OBJECT-TYPE
    SYNTAX DisplayString
    MAX-ACCESS read-write
    STATUS current
    DESCRIPTION
        "Return-to-normal alias for this contact closure"
    ::= { esPointConfigCCEntry 14 }
    --1.3.6.1.4.1.3052.17.2.2.2.1.14

espcCCNormalThreshold OBJECT-TYPE
    SYNTAX Integer32 (0..65535)
    MAX-ACCESS read-write
    STATUS current
    DESCRIPTION
        "Event threshold (seconds) for this contact closure to return to normal"
    ::= { esPointConfigCCEntry 15 }
    --1.3.6.1.4.1.3052.17.2.2.2.1.15




esPointConfigHumidTable OBJECT-TYPE
    SYNTAX SEQUENCE OF ESPointConfigHumid
    MAX-ACCESS not-accessible
    STATUS current
    DESCRIPTION
        "This table organizes 3 basic attributes of humidity points.
        A point is a particular sensor on an EventSensor.  The 3
        point attributes organizes in this table are:
        1. the configuration item (e.g., enable, name, etc.)
        2. the eventsensor on which this point resides
        3. the point number (always 1 for humidity sensors)

        Points are referenced by a point config index.  The point
        config index is a string of 2 numbers separated by a period.
        It contains all the information necessary for getting a piece
        of data off an event sensor within the context of this
        humidity point config table ; namely, which EventSensor and
        which sensor.
        "
    ::= { eventSensorPointConfig 3 }
    --1.3.6.1.4.1.3052.17.2.2.3

esPointConfigHumidEntry OBJECT-TYPE
    SYNTAX ESPointConfigHumid
    MAX-ACCESS not-accessible
    STATUS current
    DESCRIPTION
        "Entry for EventSensor point config humidity table"
    INDEX { espcHumidIndexES, espcHumidIndexPoint }
    ::= { esPointConfigHumidTable 1 }
    --1.3.6.1.4.1.3052.17.2.2.3.1

espcHumidIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigHumidEntry 1 }
    --1.3.6.1.4.1.3052.17.2.2.3.1.1

espcHumidIndexPoint OBJECT-TYPE
    SYNTAX Integer32 (1..64)
    MAX-ACCESS read-only
    STATUS current
    DESCRIPTION
        "The part of the point index that delineates which
        sensor on the EventSensor.

        So this combined with espcHumidIndexES (which EventSensor)
        uniquely defines each point attached to a unit within the
        context of contact closure point configuration."
    ::= { esPointConfigHumidEntry 2 }
    --1.3.6.1.4.1.3052.17.2.2.3.1.2

espcHumidEnable OBJECT-TYPE
    SYNTAX DisplayString
    MAX-ACCESS read-write
    STATUS current
    DESCRIPTION
        "ON/OFF enable for this humidity sensor"
    ::= { esPointConfigHumidEntry 3 }
    --1.3.6.1.4.1.3052.17.2.2.3.1.3

espcHumidDeadband OBJECT-TYPE
    SYNTAX Integer32
    MAX-ACCESS read-write
    STATUS current
    DESCRIPTION
        "Deadband for this humidity sensor"
    ::= { esPointConfigHumidEntry 4 }
    --1.3.6.1.4.1.3052.17.2.2.3.1.4

espcHumidVHighHumid OBJECT-TYPE
    SYNTAX Integer32
    MAX-ACCESS read-write
    STATUS current
    DESCRIPTION
        "Very high event threshold for this humidity sensor"
    ::= { esPointConfigHumidEntry 5 }
    --1.3.6.1.4.1.3052.17.2.2.3.1.5

espcHumidVHighActions OBJECT-TYPE
    SYNTAX DisplayString
    MAX-ACCESS read-write
    STATUS current
    DESCRIPTION
        "Very high event actions for this humidity sensor"
    ::= { esPointConfigHumidEntry 6 }
    --1.3.6.1.4.1.3052.17.2.2.3.1.6

espcHumidVHighTrapnum OBJECT-TYPE
    SYNTAX Integer32
    MAX-ACCESS read-write
    STATUS current
    DESCRIPTION
        "Very high event trap number for this humidity sensor"
    ::= { esPointConfigHumidEntry 7 }
    --1.3.6.1.4.1.3052.17.2.2.3.1.7

espcHumidVHighClass OBJECT-TYPE
    SYNTAX DisplayString
    MAX-ACCESS read-write
    STATUS current
    DESCRIPTION
        "Very high event class for this humidity sensor"
    ::= { esPointConfigHumidEntry 8 }
    --1.3.6.1.4.1.3052.17.2.2.3.1.8

espcHumidHighHumid OBJECT-TYPE
    SYNTAX Integer32
    MAX-ACCESS read-write
    STATUS current
    DESCRIPTION
        "High event threshold for this humidity sensor"
    ::= { esPointConfigHumidEntry 9 }
    --1.3.6.1.4.1.3052.17.2.2.3.1.9

espcHumidHighActions OBJECT-TYPE
    SYNTAX DisplayString
    MAX-ACCESS read-write
    STATUS current
    DESCRIPTION
        "High event actions for this humidity sensor"
    ::= { esPointConfigHumidEntry 10 }
    --1.3.6.1.4.1.3052.17.2.2.3.1.10

espcHumidHighTrapnum OBJECT-TYPE
    SYNTAX Integer32
    MAX-ACCESS read-write
    STATUS current
    DESCRIPTION
        "High event trap number for this humidity sensor"
    ::= { esPointConfigHumidEntry 11 }
    --1.3.6.1.4.1.3052.17.2.2.3.1.11

espcHumidHighClass OBJECT-TYPE
    SYNTAX DisplayString
    MAX-ACCESS read-write
    STATUS current
    DESCRIPTION
        "High event class for this humidity sensor"
    ::= { esPointConfigHumidEntry 12 }
    --1.3.6.1.4.1.3052.17.2.2.3.1.12

espcHumidNormalActions OBJECT-TYPE
    SYNTAX DisplayString
    MAX-ACCESS read-write
    STATUS current
    DESCRIPTION
        "Return-to-normal actions for this humidity sensor"
    ::= { esPointConfigHumidEntry 13 }
    --1.3.6.1.4.1.3052.17.2.2.3.1.13

espcHumidNormalTrapnum OBJECT-TYPE
    SYNTAX Integer32
    MAX-ACCESS read-write
    STATUS current
    DESCRIPTION
        "Return-to-normal trap number for this humidity sensor"
    ::= { esPointConfigHumidEntry 14 }
    --1.3.6.1.4.1.3052.17.2.2.3.1.14

espcHumidNormalClass OBJECT-TYPE
    SYNTAX DisplayString
    MAX-ACCESS read-write
    STATUS current
    DESCRIPTION
        "Return-to-normal class for this humidity sensor"
    ::= { esPointConfigHumidEntry 15 }
    --1.3.6.1.4.1.3052.17.2.2.3.1.15

espcHumidLowHumid OBJECT-TYPE
    SYNTAX Integer32
    MAX-ACCESS read-write
    STATUS current
    DESCRIPTION
        "Low event threshold for this humidity sensor"
    ::= { esPointConfigHumidEntry 16 }
    --1.3.6.1.4.1.3052.17.2.2.3.1.16

espcHumidLowActions OBJECT-TYPE
    SYNTAX DisplayString
    MAX-ACCESS read-write
    STATUS current
    DESCRIPTION
        "Low event actions for this humidity sensor"
    ::= { esPointConfigHumidEntry 17 }
    --1.3.6.1.4.1.3052.17.2.2.3.1.17

espcHumidLowTrapnum OBJECT-TYPE
    SYNTAX Integer32
    MAX-ACCESS read-write
    STATUS current
    DESCRIPTION
        "Low event trap number for this humidity sensor"
    ::= { esPointConfigHumidEntry 18 }
    --1.3.6.1.4.1.3052.17.2.2.3.1.18

espcHumidLowClass OBJECT-TYPE
    SYNTAX DisplayString
    MAX-ACCESS read-write
    STATUS current
    DESCRIPTION
        "Low event class for this humidity sensor"
    ::= { esPointConfigHumidEntry 19 }
    --1.3.6.1.4.1.3052.17.2.2.3.1.19

espcHumidVLowHumid OBJECT-TYPE
    SYNTAX Integer32
    MAX-ACCESS read-write
    STATUS current
    DESCRIPTION
        "Very low event threshold for this humidity sensor"
    ::= { esPointConfigHumidEntry 20 }
    --1.3.6.1.4.1.3052.17.2.2.3.1.20

espcHumidVLowActions OBJECT-TYPE
    SYNTAX DisplayString
    MAX-ACCESS read-write
    STATUS current
    DESCRIPTION
        "Very low event actions for this humidity sensor"
    ::= { esPointConfigHumidEntry 21 }
    --1.3.6.1.4.1.3052.17.2.2.3.1.21

espcHumidVLowTrapnum OBJECT-TYPE
    SYNTAX Integer32
    MAX-ACCESS read-write
    STATUS current
    DESCRIPTION
        "Very low event trap number for this humidity sensor"
    ::= { esPointConfigHumidEntry 22 }
    --1.3.6.1.4.1.3052.17.2.2.3.1.22

espcHumidVLowClass OBJECT-TYPE
    SYNTAX DisplayString
    MAX-ACCESS read-write
    STATUS current
    DESCRIPTION
        "Very low event class for this humidity sensor"
    ::= { esPointConfigHumidEntry 23 }
    --1.3.6.1.4.1.3052.17.2.2.3.1.23


esPointConfigAITable OBJECT-TYPE
    SYNTAX SEQUENCE OF ESPointConfigAnalogInput
    MAX-ACCESS not-accessible
    STATUS current
    DESCRIPTION
        "This table organizes 3 basic attributes of analog input
        points.  A point is a particular sensor on an EventSensor.
        The 3 point attributes organizes in this table are:
        1. the configuration item (e.g., enable, name, etc.)
        2. the eventsensor on which this point resides
        3. the point number

        Points are referenced by a point config index.  The point
        config index is a string of 2 numbers separated by a period.
        It contains all the information necessary for getting a
        piece of data off an event sensor within the context of this
        analog input point config table ; namely, which EventSensor
        and which sensor.
        "
    ::= { eventSensorPointConfig 5 }
    --1.3.6.1.4.1.3052.17.2.2.5

esPointConfigAIEntry OBJECT-TYPE
    SYNTAX ESPointConfigAnalogInput
    MAX-ACCESS not-accessible
    STATUS current
    DESCRIPTION
        "Entry for EventSensor point config analog input table"
    INDEX { espcHumidIndexES, espcHumidIndexPoint }
    ::= { esPointConfigAITable 1 }
    --1.3.6.1.4.1.3052.17.2.2.5.1

espcAIIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigAIEntry 1 }
    --1.3.6.1.4.1.3052.17.2.2.5.1.1

espcAIIndexPoint OBJECT-TYPE
    SYNTAX Integer32 (1..64)
    MAX-ACCESS read-only
    STATUS current
    DESCRIPTION
        "The part of the point index that delineates which
        sensor on the EventSensor.

        So this combined with espcAIIndexES (which EventSensor)
        uniquely defines each point attached to a unit within the
        context of contact closure point configuration."
    ::= { esPointConfigAIEntry 2 }
    --1.3.6.1.4.1.3052.17.2.2.5.1.2

espcAIEnable OBJECT-TYPE
    SYNTAX DisplayString
    MAX-ACCESS read-write
    STATUS current
    DESCRIPTION
        "ON/OFF for this analog input sensor"
    ::= { esPointConfigAIEntry 3 }
    --1.3.6.1.4.1.3052.17.2.2.5.1.3

espcAIPolarity OBJECT-TYPE
    SYNTAX DisplayString
    MAX-ACCESS read-write
    STATUS current
    DESCRIPTION
        "Polarity for this analog input sensor"
    ::= { esPointConfigAIEntry 4 }
    --1.3.6.1.4.1.3052.17.2.2.5.1.4

espcAIDeadband OBJECT-TYPE
    SYNTAX Integer32
    MAX-ACCESS read-write
    STATUS current
    DESCRIPTION
        "Deadband for this analog input sensor"
    ::= { esPointConfigAIEntry 5 }
    --1.3.6.1.4.1.3052.17.2.2.5.1.5

espcAIVhighValue OBJECT-TYPE
    SYNTAX Integer32
    MAX-ACCESS read-write
    STATUS current
    DESCRIPTION
        "Very high event threshold (decivolts or tenths of
        milliamps) for this analog input sensor"
    ::= { esPointConfigAIEntry 6 }
    --1.3.6.1.4.1.3052.17.2.2.5.1.6

espcAIVhighActions OBJECT-TYPE
    SYNTAX DisplayString
    MAX-ACCESS read-write
    STATUS current
    DESCRIPTION
        "Very high event actions for this analog input sensor"
    ::= { esPointConfigAIEntry 7 }
    --1.3.6.1.4.1.3052.17.2.2.5.1.7

espcAIVhighTrapnum OBJECT-TYPE
    SYNTAX Integer32
    MAX-ACCESS read-write
    STATUS current
    DESCRIPTION
        "Very high event trap number for this analog input sensor"
    ::= { esPointConfigAIEntry 8 }
    --1.3.6.1.4.1.3052.17.2.2.5.1.8

espcAIVhighClass OBJECT-TYPE
    SYNTAX DisplayString
    MAX-ACCESS read-write
    STATUS current
    DESCRIPTION
        "Very high event class for this analog input sensor"
    ::= { esPointConfigAIEntry 9 }
    --1.3.6.1.4.1.3052.17.2.2.5.1.9

espcAIHighValue OBJECT-TYPE
    SYNTAX Integer32
    MAX-ACCESS read-write
    STATUS current
    DESCRIPTION
        "High event threshold (decivolts or tenths of milliamps) for
        this analog input sensor"
    ::= { esPointConfigAIEntry 10 }
    --1.3.6.1.4.1.3052.17.2.2.5.1.10

espcAIHighActions OBJECT-TYPE
    SYNTAX DisplayString
    MAX-ACCESS read-write
    STATUS current
    DESCRIPTION
        "High event actions for this analog input sensor"
    ::= { esPointConfigAIEntry 11 }
    --1.3.6.1.4.1.3052.17.2.2.5.1.11

espcAIHighTrapnum OBJECT-TYPE
    SYNTAX Integer32
    MAX-ACCESS read-write
    STATUS current
    DESCRIPTION
        "High event trap number for this analog input sensor"
    ::= { esPointConfigAIEntry 12 }
    --1.3.6.1.4.1.3052.17.2.2.5.1.12

espcAIHighClass OBJECT-TYPE
    SYNTAX DisplayString
    MAX-ACCESS read-write
    STATUS current
    DESCRIPTION
        "High event class for this analog input sensor"
    ::= { esPointConfigAIEntry 13 }
    --1.3.6.1.4.1.3052.17.2.2.5.1.13

espcAINormalActions OBJECT-TYPE
    SYNTAX DisplayString
    MAX-ACCESS read-write
    STATUS current
    DESCRIPTION
        "Return-to-normal actions for this analog input sensor"
    ::= { esPointConfigAIEntry 14 }
    --1.3.6.1.4.1.3052.17.2.2.5.1.14

espcAINormalTrapnum OBJECT-TYPE
    SYNTAX Integer32
    MAX-ACCESS read-write
    STATUS current
    DESCRIPTION
        "Return-to-normal trap number for this analog input sensor"
    ::= { esPointConfigAIEntry 15 }
    --1.3.6.1.4.1.3052.17.2.2.5.1.15

espcAINormalClass OBJECT-TYPE
    SYNTAX DisplayString
    MAX-ACCESS read-write
    STATUS current
    DESCRIPTION
        "Return-to-normal class for this analog input sensor"
    ::= { esPointConfigAIEntry 16 }
    --1.3.6.1.4.1.3052.17.2.2.5.1.16

espcAILowValue OBJECT-TYPE
    SYNTAX Integer32
    MAX-ACCESS read-write
    STATUS current
    DESCRIPTION
        "Low event threshold (decivolts or tenths of milliamps) for
        this analog input sensor"
    ::= { esPointConfigAIEntry 17 }
    --1.3.6.1.4.1.3052.17.2.2.5.1.17

espcAILowActions OBJECT-TYPE
    SYNTAX DisplayString
    MAX-ACCESS read-write
    STATUS current
    DESCRIPTION
        "Low event actions for this analog input sensor"
    ::= { esPointConfigAIEntry 18 }
    --1.3.6.1.4.1.3052.17.2.2.5.1.18

espcAILowTrapnum OBJECT-TYPE
    SYNTAX Integer32
    MAX-ACCESS read-write
    STATUS current
    DESCRIPTION
        "Low event trap number for this analog input sensor"
    ::= { esPointConfigAIEntry 19 }
    --1.3.6.1.4.1.3052.17.2.2.5.1.19

espcAILowClass OBJECT-TYPE
    SYNTAX DisplayString
    MAX-ACCESS read-write
    STATUS current
    DESCRIPTION
        "Low event class for this analog input sensor"
    ::= { esPointConfigAIEntry 20 }
    --1.3.6.1.4.1.3052.17.2.2.5.1.20

espcAIVlowValue OBJECT-TYPE
    SYNTAX Integer32
    MAX-ACCESS read-write
    STATUS current
    DESCRIPTION
        "Very low event threshold (decivolts or tenths of milliamps)
        for this analog input sensor"
    ::= { esPointConfigAIEntry 21 }
    --1.3.6.1.4.1.3052.17.2.2.5.1.21

espcAIVlowActions OBJECT-TYPE
    SYNTAX DisplayString
    MAX-ACCESS read-write
    STATUS current
    DESCRIPTION
        "Very low event actions for this analog input sensor"
    ::= { esPointConfigAIEntry 22 }
    --1.3.6.1.4.1.3052.17.2.2.5.1.22

espcAIVlowTrapnum OBJECT-TYPE
    SYNTAX Integer32
    MAX-ACCESS read-write
    STATUS current
    DESCRIPTION
        "Very low event actions for this analog input sensor"
    ::= { esPointConfigAIEntry 23 }
    --1.3.6.1.4.1.3052.17.2.2.5.1.23

espcAIVlowClass OBJECT-TYPE
    SYNTAX DisplayString
    MAX-ACCESS read-write
    STATUS current
    DESCRIPTION
        "Very low event class for this analog input sensor"
    ::= { esPointConfigAIEntry 24 }
    --1.3.6.1.4.1.3052.17.2.2.5.1.24

espcAIConvUnitName OBJECT-TYPE
    SYNTAX DisplayString
    MAX-ACCESS read-write
    STATUS current
    DESCRIPTION
        "Converstion unit name for this analog input sensor"
    ::= { esPointConfigAIEntry 25 }
    --1.3.6.1.4.1.3052.17.2.2.5.1.25

espcAIConvHighValue OBJECT-TYPE
    SYNTAX Integer32
    MAX-ACCESS read-write
    STATUS current
    DESCRIPTION
        "Conversion high value for this analog input sensor"
    ::= { esPointConfigAIEntry 26 }
    --1.3.6.1.4.1.3052.17.2.2.5.1.26

espcAIConvHighUnit OBJECT-TYPE
    SYNTAX Integer32
    MAX-ACCESS read-write
    STATUS current
    DESCRIPTION
        "Conversion high unit value for this analog input sensor"
    ::= { esPointConfigAIEntry 27 }
    --1.3.6.1.4.1.3052.17.2.2.5.1.27

espcAIConvHighSign OBJECT-TYPE
    SYNTAX DisplayString
    MAX-ACCESS read-write
    STATUS current
    DESCRIPTION
        "Conversion high sign for this analog input sensor"
    ::= { esPointConfigAIEntry 28 }
    --1.3.6.1.4.1.3052.17.2.2.5.1.28

espcAIConvLowValue OBJECT-TYPE
    SYNTAX Integer32
    MAX-ACCESS read-write
    STATUS current
    DESCRIPTION
        "Conversion low value for this analog input sensor"
    ::= { esPointConfigAIEntry 29 }
    --1.3.6.1.4.1.3052.17.2.2.5.1.29

espcAIConvLowUnit OBJECT-TYPE
    SYNTAX Integer32
    MAX-ACCESS read-write
    STATUS current
    DESCRIPTION
        "Conversion unit low unit value for this analog input sensor"
    ::= { esPointConfigAIEntry 30 }
    --1.3.6.1.4.1.3052.17.2.2.5.1.30

espcAIConvLowSign OBJECT-TYPE
    SYNTAX DisplayString
    MAX-ACCESS read-write
    STATUS current
    DESCRIPTION
        "Conversion low sign for this analog input sensor"
    ::= { esPointConfigAIEntry 31 }
    --1.3.6.1.4.1.3052.17.2.2.5.1.31


--***************************************************************************************
--Serial Port Section       2.3
--***************************************************************************************

numberPorts OBJECT-TYPE
    SYNTAX Integer32
    MAX-ACCESS read-only
    STATUS current
    DESCRIPTION
        "Number of RS-232 ports found.
        Range: 2 or 4"
    ::= { serialPorts 1 }
    --1.3.6.1.4.1.3052.17.2.3.1

portConfigTable OBJECT-TYPE
    SYNTAX SEQUENCE OF PortConfig
    MAX-ACCESS not-accessible
    STATUS current
    DESCRIPTION
        "Port config table"
    ::= { serialPorts 2 }
    --1.3.6.1.4.1.3052.17.2.3.2

portConfigEntry OBJECT-TYPE
    SYNTAX PortConfig
    MAX-ACCESS not-accessible
    STATUS current
    DESCRIPTION
        "Port config entry"
    INDEX { portConfigIndex }
    ::= { portConfigTable 1 }
    --1.3.6.1.4.1.3052.17.2.3.2.1

portConfigIndex OBJECT-TYPE
    SYNTAX Integer32 (1..16)
    MAX-ACCESS read-only
    STATUS current
    DESCRIPTION
        "Index for ports"
    ::= { portConfigEntry 1 }
    --1.3.6.1.4.1.3052.17.2.3.2.1.1

portConfigBaud OBJECT-TYPE
    SYNTAX Integer32
    MAX-ACCESS read-write
    STATUS current
    DESCRIPTION
        "Baud rate, 19200, 9600, etc."
    ::= { portConfigEntry 2 }
    --1.3.6.1.4.1.3052.17.2.3.2.1.2

portConfigDataFormat OBJECT-TYPE
    SYNTAX Integer32
    MAX-ACCESS read-write
    STATUS current
    DESCRIPTION
        "Value representing word length, parity, and
        stop bits: 0=8N1, 1=7E1, 2=7O1, 3=7N1, 4=8O2"
    ::= { portConfigEntry 3 }
    --1.3.6.1.4.1.3052.17.2.3.2.1.3

portConfigStripPtOutputLfs OBJECT-TYPE
    SYNTAX Integer32
    MAX-ACCESS read-write
    STATUS current
    DESCRIPTION
        "Strip passthrough LFs sent to device on this port:
        1=yes, 0=no."
    ::= { portConfigEntry 4 }
    --1.3.6.1.4.1.3052.17.2.3.2.1.4

portConfigStripPtInputLfs OBJECT-TYPE
    SYNTAX Integer32
    MAX-ACCESS read-write
    STATUS current
    DESCRIPTION
        "Strip passthrough LFs received from device on this
        port: 1=yes, 0=no."
    ::= { portConfigEntry 5 }
    --1.3.6.1.4.1.3052.17.2.3.2.1.5

portConfigMaskEnable OBJECT-TYPE
    SYNTAX Integer32
    MAX-ACCESS read-write
    STATUS current
    DESCRIPTION
        "1=Use the character mask on this port.  0=Do
        not use the mask.  When the mask is enabled,
        the following ASCII characters are ignored
        on the port:
        0, 1, 4-9, 11, 12, 14-31, 128-255.
        When the mask is disabled, all characters are
        accepted on the port."
    ::= { portConfigEntry 7 }
    --1.3.6.1.4.1.3052.17.2.3.2.1.7

portConfigDAEnable OBJECT-TYPE
    SYNTAX Integer32
    MAX-ACCESS read-write
    STATUS current
    DESCRIPTION
        "1=Enable the Data Alarm Evaluator for data
        on this port.  0=Do not evaluate data on this
        port."
    ::= { portConfigEntry 8 }
    --1.3.6.1.4.1.3052.17.2.3.2.1.8

portConfigStoreAlarmsDPT OBJECT-TYPE
    SYNTAX DisplayString
    MAX-ACCESS read-write
    STATUS current
    DESCRIPTION
        "ON/OFF: store alarms received during passthrough"
    ::= { portConfigEntry 9 }
    --1.3.6.1.4.1.3052.17.2.3.2.1.9

portConfigRecordTimeout OBJECT-TYPE
    SYNTAX Integer32
    MAX-ACCESS read-write
    STATUS current
    DESCRIPTION
        "Timeout after last unterminated data received upon
        which data collected so far is stored as a record."
    ::= { portConfigEntry 10 }
    --1.3.6.1.4.1.3052.17.2.3.2.1.10

portConfigDataType OBJECT-TYPE
    SYNTAX DisplayString
    MAX-ACCESS read-write
    STATUS current
    DESCRIPTION
        "How the port interprets incoming data: ASCII/BINARY"
    ::= { portConfigEntry 11 }
    --1.3.6.1.4.1.3052.17.2.3.2.1.11

portConfigEtxToCRLF OBJECT-TYPE
    SYNTAX DisplayString
    MAX-ACCESS read-write
    STATUS current
    DESCRIPTION
        "ON/OFF whether the port translates incoming ETX to CRLF"
    ::= { portConfigEntry 12 }
    --1.3.6.1.4.1.3052.17.2.3.2.1.12

portConfigMLREnable OBJECT-TYPE
    SYNTAX DisplayString
    MAX-ACCESS read-write
    STATUS current
    DESCRIPTION
        "ON/OFF Whether Multiline Records are collected on this port."
    ::= { portConfigEntry 13 }
    --1.3.6.1.4.1.3052.17.2.3.2.1.13

portConfigMLRStartField1Pos OBJECT-TYPE
    SYNTAX Integer32
    MAX-ACCESS read-write
    STATUS current
    DESCRIPTION
        "Position of MLR start field 1"
    ::= { portConfigEntry 14 }
    --1.3.6.1.4.1.3052.17.2.3.2.1.14

portConfigMLRStartField1Text OBJECT-TYPE
    SYNTAX DisplayString
    MAX-ACCESS read-write
    STATUS current
    DESCRIPTION
        "Text to match MLR start field 1"
    ::= { portConfigEntry 15 }
    --1.3.6.1.4.1.3052.17.2.3.2.1.15

portConfigMLRStartField2Pos OBJECT-TYPE
    SYNTAX Integer32
    MAX-ACCESS read-write
    STATUS current
    DESCRIPTION
        "Position of MLR start field 2"
    ::= { portConfigEntry 16 }
    --1.3.6.1.4.1.3052.17.2.3.2.1.16

portConfigMLRStartField2Text OBJECT-TYPE
    SYNTAX DisplayString
    MAX-ACCESS read-write
    STATUS current
    DESCRIPTION
        "Text to match MLR start field 2"
    ::= { portConfigEntry 17 }
    --1.3.6.1.4.1.3052.17.2.3.2.1.17

portConfigMLRNumLinesBefore OBJECT-TYPE
    SYNTAX Integer32
    MAX-ACCESS read-write
    STATUS current
    DESCRIPTION
        "Number of lines before the starting line which should
        be included in the MLR"
    ::= { portConfigEntry 18 }
    --1.3.6.1.4.1.3052.17.2.3.2.1.18

portConfigMLREndDetection OBJECT-TYPE
    SYNTAX DisplayString
    MAX-ACCESS read-write
    STATUS current
    DESCRIPTION
        "How the MLR parser determines what ends an MLR: by FORMULA,
        number of lines received so far (COUNT), or number of blank
        lines received so far (BLANKS)"
    ::= { portConfigEntry 19 }
    --1.3.6.1.4.1.3052.17.2.3.2.1.19

portConfigMLRLineCount OBJECT-TYPE
    SYNTAX Integer32
    MAX-ACCESS read-write
    STATUS current
    DESCRIPTION
        "Number of lines in the MLR (used by the end detection mode)"
    ::= { portConfigEntry 20 }
    --1.3.6.1.4.1.3052.17.2.3.2.1.20

portConfigMLREndField1Pos OBJECT-TYPE
    SYNTAX Integer32
    MAX-ACCESS read-write
    STATUS current
    DESCRIPTION
        "Position of MLR end field 1"
    ::= { portConfigEntry 21 }
    --1.3.6.1.4.1.3052.17.2.3.2.1.21

portConfigMLREndField1Text OBJECT-TYPE
    SYNTAX DisplayString
    MAX-ACCESS read-write
    STATUS current
    DESCRIPTION
        "Text to match MLR end field 1"
    ::= { portConfigEntry 22 }
    --1.3.6.1.4.1.3052.17.2.3.2.1.22

portConfigMLREndField2Pos OBJECT-TYPE
    SYNTAX Integer32
    MAX-ACCESS read-write
    STATUS current
    DESCRIPTION
        "Position of MLR end field 2"
    ::= { portConfigEntry 23 }
    --1.3.6.1.4.1.3052.17.2.3.2.1.23

portConfigMLREndField2Text OBJECT-TYPE
    SYNTAX DisplayString
    MAX-ACCESS read-write
    STATUS current
    DESCRIPTION
        "Text to match MLR end field 2"
    ::= { portConfigEntry 24 }
    --1.3.6.1.4.1.3052.17.2.3.2.1.24

portConfigMLRUseComplexRules OBJECT-TYPE
    SYNTAX DisplayString
    MAX-ACCESS read-write
    STATUS current
    DESCRIPTION
        "ON/OFF MLR parser uses complex rules (field possitions/
        formulas, etc.)"
    ::= { portConfigEntry 25 }
    --1.3.6.1.4.1.3052.17.2.3.2.1.25

portConfigBufferPT OBJECT-TYPE
    SYNTAX DisplayString
    MAX-ACCESS read-write
    STATUS current
    DESCRIPTION
        "ON/OFF records received during passthrough mode are
        buffered/stored in the database"
    ::= { portConfigEntry 26 }
    --1.3.6.1.4.1.3052.17.2.3.2.1.26

portConfigId OBJECT-TYPE
    SYNTAX DisplayString
    MAX-ACCESS read-write
    STATUS current
    DESCRIPTION
        "The text identifer for the port"
    ::= { portConfigEntry 27 }
    --1.3.6.1.4.1.3052.17.2.3.2.1.27

--***************************************************************************************
--Network Section   2.4
--***************************************************************************************

eth1Mode OBJECT-TYPE
    SYNTAX DisplayString
    MAX-ACCESS read-only
    STATUS current
    DESCRIPTION
         "Mode of the Ethernet1 interface: STATIC,DHCP,VLAN"
    ::= { ethernet1 1 }
    --1.3.6.1.4.1.3052.17.2.4.1.1.1.1

eth1Address OBJECT-TYPE
    SYNTAX IpAddress
    MAX-ACCESS read-write
    STATUS current
    DESCRIPTION
        "Ethernet1 IP address"
    ::= { ethernet1 2 }
    --1.3.6.1.4.1.3052.17.2.4.1.1.1.2

eth1SubnetMask OBJECT-TYPE
    SYNTAX IpAddress
    MAX-ACCESS read-write
    STATUS current
    DESCRIPTION
        "Ethernet1 subnet mask"
    ::= { ethernet1 3 }
    --1.3.6.1.4.1.3052.17.2.4.1.1.1.3

eth1Router OBJECT-TYPE
    SYNTAX IpAddress
    MAX-ACCESS read-write
    STATUS current
    DESCRIPTION
        "Ethernet1 router"
    ::= { ethernet1 4 }
    --1.3.6.1.4.1.3052.17.2.4.1.1.1.4

-- Ethernet1 VLAN1

eth1VLAN1ID OBJECT-TYPE
    SYNTAX Integer32
    MAX-ACCESS read-write
    STATUS current
    DESCRIPTION
        "Ethernet1 VLAN1 ID"
    ::= { eth1VLAN1 1 }
    --1.3.6.1.4.1.3052.17.2.4.1.1.1.5.1.1

eth1VLAN1Priority OBJECT-TYPE
    SYNTAX Integer32
    MAX-ACCESS read-write
    STATUS current
    DESCRIPTION
        "Ethernet1 VLAN1 priority"
    ::= { eth1VLAN1 2 }
    --1.3.6.1.4.1.3052.17.2.4.1.1.1.5.1.2

eth1VLAN1Address OBJECT-TYPE
    SYNTAX IpAddress
    MAX-ACCESS read-write
    STATUS current
    DESCRIPTION
        "Ethernet1 VLAN1 IP address"
    ::= { eth1VLAN1 3 }
    --1.3.6.1.4.1.3052.17.2.4.1.1.1.5.1.3

eth1VLAN1SubnetMask OBJECT-TYPE
    SYNTAX IpAddress
    MAX-ACCESS read-write
    STATUS current
    DESCRIPTION
        "Ethernet1 VLAN1 subnet mask"
    ::= { eth1VLAN1 4 }
    --1.3.6.1.4.1.3052.17.2.4.1.1.1.5.1.4

eth1VLAN1Router OBJECT-TYPE
    SYNTAX IpAddress
    MAX-ACCESS read-write
    STATUS current
    DESCRIPTION
        "Ethernet1 VLAN1 router"
    ::= { eth1VLAN1 5 }
    --1.3.6.1.4.1.3052.17.2.4.1.1.1.5.1.5

-- Ethernet1 VLAN2

eth1VLAN2ID OBJECT-TYPE
    SYNTAX Integer32
    MAX-ACCESS read-write
    STATUS current
    DESCRIPTION
        "Ethernet1 VLAN2 ID"
    ::= { eth1VLAN2 1 }
    --1.3.6.1.4.1.3052.17.2.4.1.1.1.5.2.1

eth1VLAN2Priority OBJECT-TYPE
    SYNTAX Integer32
    MAX-ACCESS read-write
    STATUS current
    DESCRIPTION
        "Ethernet1 VLAN2 priority"
    ::= { eth1VLAN2 2 }
    --1.3.6.1.4.1.3052.17.2.4.1.1.1.5.2.2

eth1VLAN2Address OBJECT-TYPE
    SYNTAX IpAddress
    MAX-ACCESS read-write
    STATUS current
    DESCRIPTION
        "Ethernet1 VLAN2 IP address"
    ::= { eth1VLAN2 3 }
    --1.3.6.1.4.1.3052.17.2.4.1.1.1.5.2.3

eth1VLAN2SubnetMask OBJECT-TYPE
    SYNTAX IpAddress
    MAX-ACCESS read-write
    STATUS current
    DESCRIPTION
        "Ethernet1 VLAN2 subnet mask"
    ::= { eth1VLAN2 4 }
    --1.3.6.1.4.1.3052.17.2.4.1.1.1.5.2.4

eth1VLAN2Router OBJECT-TYPE
    SYNTAX IpAddress
    MAX-ACCESS read-write
    STATUS current
    DESCRIPTION
        "Ethernet1 VLAN2 router"
    ::= { eth1VLAN2 5 }
    --1.3.6.1.4.1.3052.17.2.4.1.1.1.5.2.5

-- Ethernet1 VLAN3

eth1VLAN3ID OBJECT-TYPE
    SYNTAX Integer32
    MAX-ACCESS read-write
    STATUS current
    DESCRIPTION
        "Ethernet1 VLAN3 ID"
    ::= { eth1VLAN3 1 }
    --1.3.6.1.4.1.3052.17.2.4.1.1.1.5.3.1

eth1VLAN3Priority OBJECT-TYPE
    SYNTAX Integer32
    MAX-ACCESS read-write
    STATUS current
    DESCRIPTION
        "Ethernet1 VLAN3 priority"
    ::= { eth1VLAN3 2 }
    --1.3.6.1.4.1.3052.17.2.4.1.1.1.5.3.2

eth1VLAN3Address OBJECT-TYPE
    SYNTAX IpAddress
    MAX-ACCESS read-write
    STATUS current
    DESCRIPTION
        "Ethernet1 VLAN3 IP address"
    ::= { eth1VLAN3 3 }
    --1.3.6.1.4.1.3052.17.2.4.1.1.1.5.3.3

eth1VLAN3SubnetMask OBJECT-TYPE
    SYNTAX IpAddress
    MAX-ACCESS read-write
    STATUS current
    DESCRIPTION
        "Ethernet1 VLAN3 subnet mask"
    ::= { eth1VLAN3 4 }
    --1.3.6.1.4.1.3052.17.2.4.1.1.1.5.3.4

eth1VLAN3Router OBJECT-TYPE
    SYNTAX IpAddress
    MAX-ACCESS read-write
    STATUS current
    DESCRIPTION
        "Ethernet1 VLAN3 router"
    ::= { eth1VLAN3 5 }
    --1.3.6.1.4.1.3052.17.2.4.1.1.1.5.3.5

-- Ethernet1 VLAN4

eth1VLAN4ID OBJECT-TYPE
    SYNTAX Integer32
    MAX-ACCESS read-write
    STATUS current
    DESCRIPTION
        "Ethernet1 VLAN4 ID"
    ::= { eth1VLAN4 1 }
    --1.3.6.1.4.1.3052.17.2.4.1.1.1.5.4.1

eth1VLAN4Priority OBJECT-TYPE
    SYNTAX Integer32
    MAX-ACCESS read-write
    STATUS current
    DESCRIPTION
        "Ethernet1 VLAN4 priority"
    ::= { eth1VLAN4 2 }
    --1.3.6.1.4.1.3052.17.2.4.1.1.1.5.4.2

eth1VLAN4Address OBJECT-TYPE
    SYNTAX IpAddress
    MAX-ACCESS read-write
    STATUS current
    DESCRIPTION
        "Ethernet1 VLAN4 IP address"
    ::= { eth1VLAN4 3 }
    --1.3.6.1.4.1.3052.17.2.4.1.1.1.5.4.3

eth1VLAN4SubnetMask OBJECT-TYPE
    SYNTAX IpAddress
    MAX-ACCESS read-write
    STATUS current
    DESCRIPTION
        "Ethernet1 VLAN4 subnet mask"
    ::= { eth1VLAN4 4 }
    --1.3.6.1.4.1.3052.17.2.4.1.1.1.5.4.4

eth1VLAN4Router OBJECT-TYPE
    SYNTAX IpAddress
    MAX-ACCESS read-write
    STATUS current
    DESCRIPTION
        "Ethernet1 VLAN4 router"
    ::= { eth1VLAN4 5 }
    --1.3.6.1.4.1.3052.17.2.4.1.1.1.5.4.5

-- Ethernet1 VLAN5

eth1VLAN5ID OBJECT-TYPE
    SYNTAX Integer32
    MAX-ACCESS read-write
    STATUS current
    DESCRIPTION
        "Ethernet1 VLAN5 ID"
    ::= { eth1VLAN5 1 }
    --1.3.6.1.4.1.3052.17.2.4.1.1.1.5.5.1

eth1VLAN5Priority OBJECT-TYPE
    SYNTAX Integer32
    MAX-ACCESS read-write
    STATUS current
    DESCRIPTION
        "Ethernet1 VLAN5 priority"
    ::= { eth1VLAN5 2 }
    --1.3.6.1.4.1.3052.17.2.4.1.1.1.5.5.2

eth1VLAN5Address OBJECT-TYPE
    SYNTAX IpAddress
    MAX-ACCESS read-write
    STATUS current
    DESCRIPTION
        "Ethernet1 VLAN5 IP address"
    ::= { eth1VLAN5 3 }
    --1.3.6.1.4.1.3052.17.2.4.1.1.1.5.5.3

eth1VLAN5SubnetMask OBJECT-TYPE
    SYNTAX IpAddress
    MAX-ACCESS read-write
    STATUS current
    DESCRIPTION
        "Ethernet1 VLAN5 subnet mask"
    ::= { eth1VLAN5 4 }
    --1.3.6.1.4.1.3052.17.2.4.1.1.1.5.5.4

eth1VLAN5Router OBJECT-TYPE
    SYNTAX IpAddress
    MAX-ACCESS read-write
    STATUS current
    DESCRIPTION
        "Ethernet1 VLAN5 router"
    ::= { eth1VLAN5 5 }
    --1.3.6.1.4.1.3052.17.2.4.1.1.1.5.5.5

-- Ethernet1 VLAN6

eth1VLAN6ID OBJECT-TYPE
    SYNTAX Integer32
    MAX-ACCESS read-write
    STATUS current
    DESCRIPTION
        "Ethernet1 VLAN6 ID"
    ::= { eth1VLAN6 1 }
    --1.3.6.1.4.1.3052.17.2.4.1.1.1.5.6.1

eth1VLAN6Priority OBJECT-TYPE
    SYNTAX Integer32
    MAX-ACCESS read-write
    STATUS current
    DESCRIPTION
        "Ethernet1 VLAN6 priority"
    ::= { eth1VLAN6 2 }
    --1.3.6.1.4.1.3052.17.2.4.1.1.1.5.6.2

eth1VLAN6Address OBJECT-TYPE
    SYNTAX IpAddress
    MAX-ACCESS read-write
    STATUS current
    DESCRIPTION
        "Ethernet1 VLAN6 IP address"
    ::= { eth1VLAN6 3 }
    --1.3.6.1.4.1.3052.17.2.4.1.1.1.5.6.3

eth1VLAN6SubnetMask OBJECT-TYPE
    SYNTAX IpAddress
    MAX-ACCESS read-write
    STATUS current
    DESCRIPTION
        "Ethernet1 VLAN6 subnet mask"
    ::= { eth1VLAN6 4 }
    --1.3.6.1.4.1.3052.17.2.4.1.1.1.5.6.4

eth1VLAN6Router OBJECT-TYPE
    SYNTAX IpAddress
    MAX-ACCESS read-write
    STATUS current
    DESCRIPTION
        "Ethernet1 VLAN6 router"
    ::= { eth1VLAN6 5 }
    --1.3.6.1.4.1.3052.17.2.4.1.1.1.5.6.5

eth1MAC OBJECT-TYPE
    SYNTAX DisplayString
    MAX-ACCESS read-only
    STATUS current
    DESCRIPTION
        "Ethernet1 MAC"
    ::= { ethernet1 6 }
    --1.3.6.1.4.1.3052.17.2.4.1.1.1.6


eth2Mode OBJECT-TYPE
    SYNTAX DisplayString
    MAX-ACCESS read-only
    STATUS current
    DESCRIPTION
         "Mode of the Ethernet2 interface: STATIC,DHCP,VLAN"
    ::= { ethernet2 1 }
    --1.3.6.1.4.1.3052.17.2.4.1.1.2.1

eth2Address OBJECT-TYPE
    SYNTAX IpAddress
    MAX-ACCESS read-write
    STATUS current
    DESCRIPTION
        "Ethernet2 IP address"
    ::= { ethernet2 2 }
    --1.3.6.1.4.1.3052.17.2.4.1.1.2.2

eth2SubnetMask OBJECT-TYPE
    SYNTAX IpAddress
    MAX-ACCESS read-write
    STATUS current
    DESCRIPTION
        "Ethernet2 subnet mask"
    ::= { ethernet2 3 }
    --1.3.6.1.4.1.3052.17.2.4.1.1.2.3

eth2Router OBJECT-TYPE
    SYNTAX IpAddress
    MAX-ACCESS read-write
    STATUS current
    DESCRIPTION
        "Ethernet2 router"
    ::= { ethernet2 4 }
    --1.3.6.1.4.1.3052.17.2.4.1.1.2.4


-- Ethernet2 VLAN1

eth2VLAN1ID OBJECT-TYPE
    SYNTAX Integer32
    MAX-ACCESS read-write
    STATUS current
    DESCRIPTION
        "Ethernet2 VLAN1 ID"
    ::= { eth2VLAN1 1 }
    --1.3.6.1.4.1.3052.17.2.4.1.1.2.5.1.1

eth2VLAN1Priority OBJECT-TYPE
    SYNTAX Integer32
    MAX-ACCESS read-write
    STATUS current
    DESCRIPTION
        "Ethernet2 VLAN1 priority"
    ::= { eth2VLAN1 2 }
    --1.3.6.1.4.1.3052.17.2.4.1.1.2.5.1.2

eth2VLAN1Address OBJECT-TYPE
    SYNTAX IpAddress
    MAX-ACCESS read-write
    STATUS current
    DESCRIPTION
        "Ethernet2 VLAN1 IP address"
    ::= { eth2VLAN1 3 }
    --1.3.6.1.4.1.3052.17.2.4.1.1.2.5.1.3

eth2VLAN1SubnetMask OBJECT-TYPE
    SYNTAX IpAddress
    MAX-ACCESS read-write
    STATUS current
    DESCRIPTION
        "Ethernet2 VLAN1 subnet mask"
    ::= { eth2VLAN1 4 }
    --1.3.6.1.4.1.3052.17.2.4.1.1.2.5.1.4

eth2VLAN1Router OBJECT-TYPE
    SYNTAX IpAddress
    MAX-ACCESS read-write
    STATUS current
    DESCRIPTION
        "Ethernet2 VLAN1 router"
    ::= { eth2VLAN1 5 }
    --1.3.6.1.4.1.3052.17.2.4.1.1.2.5.1.5

-- Ethernet2 VLAN2

eth2VLAN2ID OBJECT-TYPE
    SYNTAX Integer32
    MAX-ACCESS read-write
    STATUS current
    DESCRIPTION
        "Ethernet2 VLAN2 ID"
    ::= { eth2VLAN2 1 }
    --1.3.6.1.4.1.3052.17.2.4.1.1.2.5.2.1

eth2VLAN2Priority OBJECT-TYPE
    SYNTAX Integer32
    MAX-ACCESS read-write
    STATUS current
    DESCRIPTION
        "Ethernet2 VLAN2 priority"
    ::= { eth2VLAN2 2 }
    --1.3.6.1.4.1.3052.17.2.4.1.1.2.5.2.2

eth2VLAN2Address OBJECT-TYPE
    SYNTAX IpAddress
    MAX-ACCESS read-write
    STATUS current
    DESCRIPTION
        "Ethernet2 VLAN2 IP address"
    ::= { eth2VLAN2 3 }
    --1.3.6.1.4.1.3052.17.2.4.1.1.2.5.2.3

eth2VLAN2SubnetMask OBJECT-TYPE
    SYNTAX IpAddress
    MAX-ACCESS read-write
    STATUS current
    DESCRIPTION
        "Ethernet2 VLAN2 subnet mask"
    ::= { eth2VLAN2 4 }
    --1.3.6.1.4.1.3052.17.2.4.1.1.2.5.2.4

eth2VLAN2Router OBJECT-TYPE
    SYNTAX IpAddress
    MAX-ACCESS read-write
    STATUS current
    DESCRIPTION
        "Ethernet2 VLAN2 router"
    ::= { eth2VLAN2 5 }
    --1.3.6.1.4.1.3052.17.2.4.1.1.2.5.2.5

-- Ethernet2 VLAN3

eth2VLAN3ID OBJECT-TYPE
    SYNTAX Integer32
    MAX-ACCESS read-write
    STATUS current
    DESCRIPTION
        "Ethernet2 VLAN3 ID"
    ::= { eth2VLAN3 1 }
    --1.3.6.1.4.1.3052.17.2.4.1.1.2.5.3.1

eth2VLAN3Priority OBJECT-TYPE
    SYNTAX Integer32
    MAX-ACCESS read-write
    STATUS current
    DESCRIPTION
        "Ethernet2 VLAN3 priority"
    ::= { eth2VLAN3 2 }
    --1.3.6.1.4.1.3052.17.2.4.1.1.2.5.3.2

eth2VLAN3Address OBJECT-TYPE
    SYNTAX IpAddress
    MAX-ACCESS read-write
    STATUS current
    DESCRIPTION
        "Ethernet2 VLAN3 IP address"
    ::= { eth2VLAN3 3 }
    --1.3.6.1.4.1.3052.17.2.4.1.1.2.5.3.3

eth2VLAN3SubnetMask OBJECT-TYPE
    SYNTAX IpAddress
    MAX-ACCESS read-write
    STATUS current
    DESCRIPTION
        "Ethernet2 VLAN3 subnet mask"
    ::= { eth2VLAN3 4 }
    --1.3.6.1.4.1.3052.17.2.4.1.1.2.5.3.4

eth2VLAN3Router OBJECT-TYPE
    SYNTAX IpAddress
    MAX-ACCESS read-write
    STATUS current
    DESCRIPTION
        "Ethernet2 VLAN3 router"
    ::= { eth2VLAN3 5 }
    --1.3.6.1.4.1.3052.17.2.4.1.1.2.5.3.5

-- Ethernet2 VLAN4

eth2VLAN4ID OBJECT-TYPE
    SYNTAX Integer32
    MAX-ACCESS read-write
    STATUS current
    DESCRIPTION
        "Ethernet2 VLAN4 ID"
    ::= { eth2VLAN4 1 }
    --1.3.6.1.4.1.3052.17.2.4.1.1.2.5.4.1

eth2VLAN4Priority OBJECT-TYPE
    SYNTAX Integer32
    MAX-ACCESS read-write
    STATUS current
    DESCRIPTION
        "Ethernet2 VLAN4 priority"
    ::= { eth2VLAN4 2 }
    --1.3.6.1.4.1.3052.17.2.4.1.1.2.5.4.2

eth2VLAN4Address OBJECT-TYPE
    SYNTAX IpAddress
    MAX-ACCESS read-write
    STATUS current
    DESCRIPTION
        "Ethernet2 VLAN4 IP address"
    ::= { eth2VLAN4 3 }
    --1.3.6.1.4.1.3052.17.2.4.1.1.2.5.4.3

eth2VLAN4SubnetMask OBJECT-TYPE
    SYNTAX IpAddress
    MAX-ACCESS read-write
    STATUS current
    DESCRIPTION
        "Ethernet2 VLAN4 subnet mask"
    ::= { eth2VLAN4 4 }
    --1.3.6.1.4.1.3052.17.2.4.1.1.2.5.4.4

eth2VLAN4Router OBJECT-TYPE
    SYNTAX IpAddress
    MAX-ACCESS read-write
    STATUS current
    DESCRIPTION
        "Ethernet2 VLAN4 router"
    ::= { eth2VLAN4 5 }
    --1.3.6.1.4.1.3052.17.2.4.1.1.2.5.4.5

-- Ethernet2 VLAN5

eth2VLAN5ID OBJECT-TYPE
    SYNTAX Integer32
    MAX-ACCESS read-write
    STATUS current
    DESCRIPTION
        "Ethernet2 VLAN5 ID"
    ::= { eth2VLAN5 1 }
    --1.3.6.1.4.1.3052.17.2.4.1.1.2.5.5.1

eth2VLAN5Priority OBJECT-TYPE
    SYNTAX Integer32
    MAX-ACCESS read-write
    STATUS current
    DESCRIPTION
        "Ethernet2 VLAN5 priority"
    ::= { eth2VLAN5 2 }
    --1.3.6.1.4.1.3052.17.2.4.1.1.2.5.5.2

eth2VLAN5Address OBJECT-TYPE
    SYNTAX IpAddress
    MAX-ACCESS read-write
    STATUS current
    DESCRIPTION
        "Ethernet2 VLAN5 IP address"
    ::= { eth2VLAN5 3 }
    --1.3.6.1.4.1.3052.17.2.4.1.1.2.5.5.3

eth2VLAN5SubnetMask OBJECT-TYPE
    SYNTAX IpAddress
    MAX-ACCESS read-write
    STATUS current
    DESCRIPTION
        "Ethernet2 VLAN5 subnet mask"
    ::= { eth2VLAN5 4 }
    --1.3.6.1.4.1.3052.17.2.4.1.1.2.5.5.4

eth2VLAN5Router OBJECT-TYPE
    SYNTAX IpAddress
    MAX-ACCESS read-write
    STATUS current
    DESCRIPTION
        "Ethernet2 VLAN5 router"
    ::= { eth2VLAN5 5 }
    --1.3.6.1.4.1.3052.17.2.4.1.1.2.5.5.5

-- Ethernet2 VLAN6

eth2VLAN6ID OBJECT-TYPE
    SYNTAX Integer32
    MAX-ACCESS read-write
    STATUS current
    DESCRIPTION
        "Ethernet2 VLAN6 ID"
    ::= { eth2VLAN6 1 }
    --1.3.6.1.4.1.3052.17.2.4.1.1.2.5.6.1

eth2VLAN6Priority OBJECT-TYPE
    SYNTAX Integer32
    MAX-ACCESS read-write
    STATUS current
    DESCRIPTION
        "Ethernet2 VLAN6 priority"
    ::= { eth2VLAN6 2 }
    --1.3.6.1.4.1.3052.17.2.4.1.1.2.5.6.2

eth2VLAN6Address OBJECT-TYPE
    SYNTAX IpAddress
    MAX-ACCESS read-write
    STATUS current
    DESCRIPTION
        "Ethernet2 VLAN6 IP address"
    ::= { eth2VLAN6 3 }
    --1.3.6.1.4.1.3052.17.2.4.1.1.2.5.6.3

eth2VLAN6SubnetMask OBJECT-TYPE
    SYNTAX IpAddress
    MAX-ACCESS read-write
    STATUS current
    DESCRIPTION
        "Ethernet2 VLAN6 subnet mask"
    ::= { eth2VLAN6 4 }
    --1.3.6.1.4.1.3052.17.2.4.1.1.2.5.6.4

eth2VLAN6Router OBJECT-TYPE
    SYNTAX IpAddress
    MAX-ACCESS read-write
    STATUS current
    DESCRIPTION
        "Ethernet2 VLAN6 router"
    ::= { eth2VLAN6 5 }
    --1.3.6.1.4.1.3052.17.2.4.1.1.2.5.6.5

eth2MAC OBJECT-TYPE
    SYNTAX DisplayString
    MAX-ACCESS read-only
    STATUS current
    DESCRIPTION
        "Ethernet2 MAC"
    ::= { ethernet2 6 }
    --1.3.6.1.4.1.3052.17.2.4.1.1.2.6


defaultRouter OBJECT-TYPE
    SYNTAX DisplayString
    MAX-ACCESS read-write
    STATUS current
    DESCRIPTION
        "The default router/gateway"
    ::= { network 2 }
    --1.3.6.1.4.1.3052.17.2.4.2

-- DNS

dnsTable OBJECT-TYPE
    SYNTAX SEQUENCE OF DNSConfig
    MAX-ACCESS not-accessible
    STATUS current
    DESCRIPTION
        "DNS server address table"
    ::= { network 3 }
    --1.3.6.1.4.1.3052.17.2.4.3

dnsEntry OBJECT-TYPE
    SYNTAX DNSConfig
    MAX-ACCESS not-accessible
    STATUS current
    DESCRIPTION
        "DNS server address entry"
    INDEX { dnsIndex }
    ::= { dnsTable 1 }
    --1.3.6.1.4.1.3052.17.2.4.3.1

dnsIndex OBJECT-TYPE
    SYNTAX Integer32 (1..2)
    MAX-ACCESS read-only
    STATUS current
    DESCRIPTION
        "Index for DNS server address"
    ::= { dnsEntry 1 }
    --1.3.6.1.4.1.3052.17.2.4.3.1.1

dnsAddress OBJECT-TYPE
    SYNTAX IpAddress
    MAX-ACCESS read-write
    STATUS current
    DESCRIPTION
        "DNS server address"
    ::= { dnsEntry 2 }
    --1.3.6.1.4.1.3052.17.2.4.3.1.2

hostname OBJECT-TYPE
    SYNTAX DisplayString
    MAX-ACCESS read-write
    STATUS current
    DESCRIPTION
        "The hostname of the unit"
    ::= { network 4 }
    --1.3.6.1.4.1.3052.17.2.4.4

hostTable OBJECT-TYPE
    SYNTAX SEQUENCE OF HostConfig
    MAX-ACCESS not-accessible
    STATUS current
    DESCRIPTION
        "Static host table"
    ::= { network 5 }
    --1.3.6.1.4.1.3052.17.2.4.5

hostEntry OBJECT-TYPE
    SYNTAX HostConfig
    MAX-ACCESS not-accessible
    STATUS current
    DESCRIPTION
        "Static host entry"
    INDEX { hostIndex }
    ::= { hostTable 1 }
    --1.3.6.1.4.1.3052.17.2.4.5.1

hostIndex OBJECT-TYPE
    SYNTAX Integer32 (1..2)
    MAX-ACCESS read-only
    STATUS current
    DESCRIPTION
        "Index for static host"
    ::= { hostEntry 1 }
    --1.3.6.1.4.1.3052.17.2.4.5.1.1

hostDeclaration OBJECT-TYPE
    SYNTAX DisplayString
    MAX-ACCESS read-write
    STATUS current
    DESCRIPTION
        "Static host declaration string (i.e. 'address hostname')"
    ::= { hostEntry 2 }
    --1.3.6.1.4.1.3052.17.2.4.5.1.2

-- Network Command Processor

ncpDuplex OBJECT-TYPE
    SYNTAX Integer32
    MAX-ACCESS read-write
    STATUS current
    DESCRIPTION
        "For network command processor: 1=Input characters are echoed; 0=no echo."
    ::= { network 6 }
    --1.3.6.1.4.1.3052.17.2.4.6

ncpTimeout OBJECT-TYPE
    SYNTAX Integer32
    MAX-ACCESS read-write
    STATUS current
    DESCRIPTION
        "Network command processor inactivity timeout"
    ::= { network 7 }
    --1.3.6.1.4.1.3052.17.2.4.7


-- SNMP

snmpAgentEnable OBJECT-TYPE
    SYNTAX DisplayString
    MAX-ACCESS read-write
    STATUS current
    DESCRIPTION
        "ON/OFF for snmp agent"
    ::= { snmp 1 }
    --1.3.6.1.4.1.3052.17.2.4.8.1

snmpNtfnAttempts OBJECT-TYPE
    SYNTAX Integer32
    MAX-ACCESS read-write
    STATUS current
    DESCRIPTION
        "Maximum of times the unit attempts to send a notification
        (trap/inform) in 1 cycle"
    ::= { snmpNotificationTx 1 }
    --1.3.6.1.4.1.3052.17.2.4.8.7.1

snmpNtfnTimeout OBJECT-TYPE
    SYNTAX Integer32
    MAX-ACCESS read-write
    STATUS current
    DESCRIPTION
        "Number of seconds between retries of sending a notification"
    ::= { snmpNotificationTx 2 }
    --1.3.6.1.4.1.3052.17.2.4.8.7.2

snmpNtfnCycles OBJECT-TYPE
    SYNTAX Integer32
    MAX-ACCESS read-write
    STATUS current
    DESCRIPTION
        "Number of times the unit attempts a group of attempts to send
        a notification (a cycle)"
    ::= { snmpNotificationTx 3 }
    --1.3.6.1.4.1.3052.17.2.4.8.7.3

snmpNtfnSnooze OBJECT-TYPE
    SYNTAX Integer32
    MAX-ACCESS read-write
    STATUS current
    DESCRIPTION
        "Minutes between cycles"
    ::= { snmpNotificationTx 4 }
    --1.3.6.1.4.1.3052.17.2.4.8.7.4


-- SNMP proxy

snmpProxyTable OBJECT-TYPE
    SYNTAX SEQUENCE OF SNMPProxyTable
    MAX-ACCESS not-accessible
    STATUS current
    DESCRIPTION
        "Table of SNMP proxy entries"
    ::= { snmpProxy 1 }
    --1.3.6.1.4.1.3052.17.2.4.8.8.1

snmpProxyEntry OBJECT-TYPE
    SYNTAX SNMPProxyTable
    MAX-ACCESS not-accessible
    STATUS current
    DESCRIPTION
        "Entry for SNMP proxy table"
    INDEX { snmpProxyIndex }
    ::= { snmpProxyTable 1 }
    --1.3.6.1.4.1.3052.17.2.4.8.8.1.1

snmpProxyIndex OBJECT-TYPE
    SYNTAX Integer32 (1..8)
    MAX-ACCESS read-only
    STATUS current
    DESCRIPTION
        "Index for SNMP proxy table"
    ::= { snmpProxyEntry 1 }
    --1.3.6.1.4.1.3052.17.2.4.8.8.1.1.1

snmpProxyOIDBranch OBJECT-TYPE
    SYNTAX DisplayString
    MAX-ACCESS read-write
    STATUS current
    DESCRIPTION
        "The OID branch to trigger the proxy function.  This should cover
        the device to proxy."
    ::= { snmpProxyEntry 2 }
    --1.3.6.1.4.1.3052.17.2.4.8.8.1.1.2

snmpProxyIP OBJECT-TYPE
    SYNTAX DisplayString
    MAX-ACCESS read-write
    STATUS current
    DESCRIPTION
        "The IP address of the device to proxy."
    ::= { snmpProxyEntry 3 }
    --1.3.6.1.4.1.3052.17.2.4.8.8.1.1.3

snmpProxyPort OBJECT-TYPE
    SYNTAX Integer32 (1..65535)
    MAX-ACCESS read-write
    STATUS current
    DESCRIPTION
        "The UDP port on which the device to proxy listens."
    ::= { snmpProxyEntry 4 }
    --1.3.6.1.4.1.3052.17.2.4.8.8.1.1.4


-- SNMP Poll

snmpPMode OBJECT-TYPE
    SYNTAX DisplayString
    MAX-ACCESS read-write
    STATUS current
    DESCRIPTION
        "Mode of poll operation: OFF or POLL ONLY (just make the results
        available to view)."
    ::= { snmpPoll 1 }
    --1.3.6.1.4.1.3052.17.2.4.8.9.1

snmpPRequestTable OBJECT-TYPE
    SYNTAX SEQUENCE OF SNMPPollRequestConfig
    MAX-ACCESS not-accessible
    STATUS current
    DESCRIPTION
        "Table of SNMP Poll requests."
    ::= { snmpPoll 4 }
    --1.3.6.1.4.1.3052.17.2.4.8.9.4

snmpPRequestEntry OBJECT-TYPE
    SYNTAX SNMPPollRequestConfig
    MAX-ACCESS not-accessible
    STATUS current
    DESCRIPTION
        "Entry for table pf SNMP Poll requests."
    INDEX { snmpPRequestIndex }
    ::= { snmpPRequestTable 1 }
    --1.3.6.1.4.1.3052.17.2.4.8.9.4.1

snmpPRequestIndex OBJECT-TYPE
    SYNTAX Integer32 (1..64)
    MAX-ACCESS read-only
    STATUS current
    DESCRIPTION
        "Index for table of SNMP Poll requests."
    ::= { snmpPRequestEntry 1 }
    --1.3.6.1.4.1.3052.17.2.4.8.9.4.1.1

snmpPRequestDescription OBJECT-TYPE
    SYNTAX DisplayString
    MAX-ACCESS read-write
    STATUS current
    DESCRIPTION
        "A description for this single telemetry request; no functional effect."
    ::= { snmpPRequestEntry 2 }
    --1.3.6.1.4.1.3052.17.2.4.8.9.4.1.2

snmpPRequestAgent OBJECT-TYPE
    SYNTAX DisplayString
    MAX-ACCESS read-write
    STATUS current
    DESCRIPTION
        "SNMP Agent IP address or hostname for this single telemetry request."
    ::= { snmpPRequestEntry 3 }
    --1.3.6.1.4.1.3052.17.2.4.8.9.4.1.3

snmpPRequestReadcom OBJECT-TYPE
    SYNTAX DisplayString
    MAX-ACCESS read-write
    STATUS current
    DESCRIPTION
        "SNMP read community for this single telemetry request."
    ::= { snmpPRequestEntry 4 }
    --1.3.6.1.4.1.3052.17.2.4.8.9.4.1.4

snmpPRequestOID OBJECT-TYPE
    SYNTAX DisplayString
    MAX-ACCESS read-write
    STATUS current
    DESCRIPTION
        "SNMP object identifier for this single telemetry request."
    ::= { snmpPRequestEntry 5 }
    --1.3.6.1.4.1.3052.17.2.4.8.9.4.1.5

snmpPRequestPeriod OBJECT-TYPE
    SYNTAX Integer32 (1..255)
    MAX-ACCESS read-write
    STATUS current
    DESCRIPTION
        "How many seconds between periodic SNMP polls of this
        single telemetry request."
    ::= { snmpPRequestEntry 6 }
    --1.3.6.1.4.1.3052.17.2.4.8.9.4.1.6

snmpPRequestResultStatus OBJECT-TYPE
    SYNTAX DisplayString
    MAX-ACCESS read-only
    STATUS current
    DESCRIPTION
        "Status of the last attempt for this telemetry request."
    ::= { snmpPRequestEntry 10 }
    --1.3.6.1.4.1.3052.17.2.4.8.9.4.1.10

snmpPRequestResultValue OBJECT-TYPE
    SYNTAX DisplayString
    MAX-ACCESS read-only
    STATUS current
    DESCRIPTION
        "The telemetry value if the last request was successful."
    ::= { snmpPRequestEntry 11 }
    --1.3.6.1.4.1.3052.17.2.4.8.9.4.1.11

snmpPRequestResultTime OBJECT-TYPE
    SYNTAX DisplayString
    MAX-ACCESS read-only
    STATUS current
    DESCRIPTION
        "The timestamp of the last telemetry request."
    ::= { snmpPRequestEntry 12 }
    --1.3.6.1.4.1.3052.17.2.4.8.9.4.1.12

snmpPRequestResultType OBJECT-TYPE
    SYNTAX DisplayString
    MAX-ACCESS read-only
    STATUS current
    DESCRIPTION
        "The type of the telemetry as reported by the agent."
    ::= { snmpPRequestEntry 13 }
    --1.3.6.1.4.1.3052.17.2.4.8.9.4.1.13


-- FTP

ftpPushEnable OBJECT-TYPE
    SYNTAX DisplayString
    MAX-ACCESS read-write
    STATUS current
    DESCRIPTION
        "Enable FTP push for REGULAR (protocol: FTP) or SECURE (protocol:
        SFTP) operation, or disable it (OFF)"
    ::= { ftpPush 1 }
    --1.3.6.1.4.1.3052.17.2.4.9.1

ftpPushServer OBJECT-TYPE
    SYNTAX DisplayString
    MAX-ACCESS read-write
    STATUS current
    DESCRIPTION
        "FTP server to which data should be pushed"
    ::= { ftpPush 2 }
    --1.3.6.1.4.1.3052.17.2.4.9.2

ftpPushAccount OBJECT-TYPE
    SYNTAX DisplayString
    MAX-ACCESS read-write
    STATUS current
    DESCRIPTION
        "FTP push account"
    ::= { ftpPush 5 }
    --1.3.6.1.4.1.3052.17.2.4.9.5

ftpPushDirectory OBJECT-TYPE
    SYNTAX DisplayString
    MAX-ACCESS read-write
    STATUS current
    DESCRIPTION
        "FTP push directory"
    ::= { ftpPush 6 }
    --1.3.6.1.4.1.3052.17.2.4.9.6

ftpPushperiod OBJECT-TYPE
    SYNTAX Integer32
    MAX-ACCESS read-write
    STATUS current
    DESCRIPTION
        "Minutes between pushes"
    ::= { ftpPush 7 }
    --1.3.6.1.4.1.3052.17.2.4.9.7

ftpPushPushFileTable OBJECT-TYPE
    SYNTAX SEQUENCE OF FTPPushPushFileConfig
    MAX-ACCESS not-accessible
    STATUS current
    DESCRIPTION
        "Table of files to push"
    ::= { ftpPush 8 }
    --1.3.6.1.4.1.3052.17.2.4.9.8

ftpPushPushFileEntry OBJECT-TYPE
    SYNTAX FTPPushPushFileConfig
    MAX-ACCESS not-accessible
    STATUS current
    DESCRIPTION
        "Entry for table of files to push"
    INDEX { ftpPushPushFileIndex }
    ::= { ftpPushPushFileTable 1 }
    --1.3.6.1.4.1.3052.17.2.4.9.8.1

ftpPushPushFileIndex OBJECT-TYPE
    SYNTAX Integer32 (1..16)
    MAX-ACCESS read-only
    STATUS current
    DESCRIPTION
        "Index for table of files to push"
    ::= { ftpPushPushFileEntry 1 }
    --1.3.6.1.4.1.3052.17.2.4.9.8.1.1

ftpPushPushFile OBJECT-TYPE
    SYNTAX DisplayString
    MAX-ACCESS read-write
    STATUS current
    DESCRIPTION
        "ON/OFF push this local FILEx"
    ::= { ftpPushPushFileEntry 2 }
    --1.3.6.1.4.1.3052.17.2.4.9.8.1.2

ftpPushPushAudit OBJECT-TYPE
    SYNTAX DisplayString
    MAX-ACCESS read-write
    STATUS current
    DESCRIPTION
        "ON/OFF push the audit log"
    ::= { ftpPush 9 }
    --1.3.6.1.4.1.3052.17.2.4.9.9

ftpPushPushAlarms OBJECT-TYPE
    SYNTAX DisplayString
    MAX-ACCESS read-write
    STATUS current
    DESCRIPTION
        "ON/OFF push the alarms/events file"
    ::= { ftpPush 10 }
    --1.3.6.1.4.1.3052.17.2.4.9.10

ftpPushRemoteFileTable OBJECT-TYPE
    SYNTAX SEQUENCE OF FTPPushRemoteFileConfig
    MAX-ACCESS not-accessible
    STATUS current
    DESCRIPTION
        "Table of remote names of files to push"
    ::= { ftpPush 11 }
    --1.3.6.1.4.1.3052.17.2.4.9.11

ftpPushRemoteFileEntry OBJECT-TYPE
    SYNTAX FTPPushRemoteFileConfig
    MAX-ACCESS not-accessible
    STATUS current
    DESCRIPTION
        "Entry for table of remote names of files to push"
    INDEX { ftpPushRemoteFileIndex }
    ::= { ftpPushRemoteFileTable 1 }
    --1.3.6.1.4.1.3052.17.2.4.9.11.1

ftpPushRemoteFileIndex OBJECT-TYPE
    SYNTAX Integer32 (1..16)
    MAX-ACCESS read-only
    STATUS current
    DESCRIPTION
        "Index for table of remote names of files to push"
    ::= { ftpPushRemoteFileEntry 1 }
    --1.3.6.1.4.1.3052.17.2.4.9.11.1

ftpPushRemoteFileName OBJECT-TYPE
    SYNTAX DisplayString
    MAX-ACCESS read-write
    STATUS current
    DESCRIPTION
        "remote name of pushed FILEx (name on server)"
    ::= { ftpPushRemoteFileEntry 2 }
    --1.3.6.1.4.1.3052.17.2.4.9.11.2

ftpPushRemoteAlarmName OBJECT-TYPE
    SYNTAX DisplayString
    MAX-ACCESS read-write
    STATUS current
    DESCRIPTION
        "Filename on server for alarms"
    ::= { ftpPush 12 }
    --1.3.6.1.4.1.3052.17.2.4.9.12

ftpPushPassive OBJECT-TYPE
    SYNTAX DisplayString
    MAX-ACCESS read-write
    STATUS current
    DESCRIPTION
        "ON/OFF use ftp passive mode"
    ::= { ftpPush 13 }
    --1.3.6.1.4.1.3052.17.2.4.9.13

ftpPushIncludeDate OBJECT-TYPE
    SYNTAX DisplayString
    MAX-ACCESS read-write
    STATUS current
    DESCRIPTION
        "ON/OFF include the date in the name of the pushed file"
    ::= { ftpPush 14 }
    --1.3.6.1.4.1.3052.17.2.4.9.14

ftpPushIncludeTime OBJECT-TYPE
    SYNTAX DisplayString
    MAX-ACCESS read-write
    STATUS current
    DESCRIPTION
        "ON/OFF include the time in the name of the pushed file"
    ::= { ftpPush 15 }
    --1.3.6.1.4.1.3052.17.2.4.9.15

ftpPushIncludeSeq OBJECT-TYPE
    SYNTAX DisplayString
    MAX-ACCESS read-write
    STATUS current
    DESCRIPTION
        "ON/OFF include a sequence number in the name of the pushed file"
    ::= { ftpPush 16 }
    --1.3.6.1.4.1.3052.17.2.4.9.16

-- Routing

ethRoutingEnable OBJECT-TYPE
    SYNTAX DisplayString
    MAX-ACCESS read-write
    STATUS current
    DESCRIPTION
        "ON/OFF unit routes IP traffic from Ethernet to PPP/Wireless"
    ::= { routing 2 }
    --1.3.6.1.4.1.3052.17.2.4.11.2

ethRoutingNATEnable OBJECT-TYPE
    SYNTAX DisplayString
    MAX-ACCESS read-write
    STATUS current
    DESCRIPTION
        "ON/OFF unit applies NAT on routed IP frames egressing the
        unit on its PPP interface"
    ::= { routing 3 }
    --1.3.6.1.4.1.3052.17.2.4.11.3

-- IP Restrictions

ipRestrictionTable OBJECT-TYPE
    SYNTAX SEQUENCE OF IPRestrictionConfig
    MAX-ACCESS not-accessible
    STATUS current
    DESCRIPTION
        "Table of IP restrictions"
    ::= { ipRestriction 1 }
    --1.3.6.1.4.1.3052.17.2.4.12.1.1

ipRestrictionEntry OBJECT-TYPE
    SYNTAX IPRestrictionConfig
    MAX-ACCESS not-accessible
    STATUS current
    DESCRIPTION
        "Entry for table of IP restrictions"
    INDEX { ipRestrictionIndex }
    ::= { ipRestrictionTable 1 }
    --1.3.6.1.4.1.3052.17.2.4.12.1.1

ipRestrictionIndex OBJECT-TYPE
    SYNTAX Integer32 (1..8)
    MAX-ACCESS read-only
    STATUS current
    DESCRIPTION
        "Index for table of IP restrictions"
    ::= { ipRestrictionEntry 1 }
    --1.3.6.1.4.1.3052.17.2.4.12.1.1.1.1

ipRestrictionEnable OBJECT-TYPE
    SYNTAX DisplayString
    MAX-ACCESS read-write
    STATUS current
    DESCRIPTION
        "ON/OFF enable this IP restriction"
    ::= { ipRestrictionEntry 2 }
    --1.3.6.1.4.1.3052.17.2.4.12.1.1.1.2

ipRestrictionMask OBJECT-TYPE
    SYNTAX IpAddress
    MAX-ACCESS read-write
    STATUS current
    DESCRIPTION
        "IP restriction mask"
    ::= { ipRestrictionEntry 3 }
    --1.3.6.1.4.1.3052.17.2.4.12.1.1.1.3


-- RTS


rtsFileTable OBJECT-TYPE
    SYNTAX SEQUENCE OF RTSFileConfig
    MAX-ACCESS not-accessible
    STATUS current
    DESCRIPTION
        "Table of RTS files"
    ::= { rts 1 }
    --1.3.6.1.4.1.3052.17.2.4.13.1

rtsFileEntry OBJECT-TYPE
    SYNTAX RTSFileConfig
    MAX-ACCESS not-accessible
    STATUS current
    DESCRIPTION
        "Entry for table of RTS files"
    INDEX { rtsFileIndex }
    ::= { rtsFileTable 1 }
    --1.3.6.1.4.1.3052.17.2.4.13.1

rtsFileIndex OBJECT-TYPE
    SYNTAX Integer32 (1..16)
    MAX-ACCESS read-only
    STATUS current
    DESCRIPTION
        "Index for table of RTS files"
    ::= { rtsFileEntry 1 }
    --1.3.6.1.4.1.3052.17.2.4.13.1.1.1

rtsFileMode OBJECT-TYPE
    SYNTAX DisplayString
    MAX-ACCESS read-write
    STATUS current
    DESCRIPTION
        "RTS mode (OFF,LISTEN,PUSH) for FILEx"
    ::= { rtsFileEntry 2 }
    --1.3.6.1.4.1.3052.17.2.4.13.1.1.2

rtsFileShowAnswer OBJECT-TYPE
    SYNTAX DisplayString
    MAX-ACCESS read-write
    STATUS current
    DESCRIPTION
        "Show answer string upon RTS connect for FILEx"
    ::= { rtsFileEntry 3 }
    --1.3.6.1.4.1.3052.17.2.4.13.1.1.3

rtsFileReqXON OBJECT-TYPE
    SYNTAX DisplayString
    MAX-ACCESS read-write
    STATUS current
    DESCRIPTION
        "ON/OFF require XON to start flow for FILEx"
    ::= { rtsFileEntry 4 }
    --1.3.6.1.4.1.3052.17.2.4.13.1.1.4

rtsFileTimeout OBJECT-TYPE
    SYNTAX Integer32
    MAX-ACCESS read-write
    STATUS current
    DESCRIPTION
        "Idle connection close timer (0 means no timeout) for FILEx"
    ::= { rtsFileEntry 5 }
    --1.3.6.1.4.1.3052.17.2.4.13.1.1.5

rtsFileEmptyClose OBJECT-TYPE
    SYNTAX DisplayString
    MAX-ACCESS read-write
    STATUS current
    DESCRIPTION
        "ON/OFF close the socket when FILEx is empty"
    ::= { rtsFileEntry 6 }
    --1.3.6.1.4.1.3052.17.2.4.13.1.1.6

rtsFilePushHost OBJECT-TYPE
    SYNTAX DisplayString
    MAX-ACCESS read-write
    STATUS current
    DESCRIPTION
        "Host to which FILEx should be pushed via RTS"
    ::= { rtsFileEntry 7 }
    --1.3.6.1.4.1.3052.17.2.4.13.1.1.7

rtsFilePushPort OBJECT-TYPE
    SYNTAX Integer32
    MAX-ACCESS read-write
    STATUS current
    DESCRIPTION
        "TCP port to which FILEx should be pushed via RTS"
    ::= { rtsFileEntry 8 }
    --1.3.6.1.4.1.3052.17.2.4.13.1.1.8

rtsFilePushRetryTimer OBJECT-TYPE
    SYNTAX Integer32
    MAX-ACCESS read-write
    STATUS current
    DESCRIPTION
        "Retry timer (seconds) for retrying failed RTS push connect
        attempts"
    ::= { rtsFileEntry 9 }
    --1.3.6.1.4.1.3052.17.2.4.13.1.1.9

-- RTS Alarms

rtsAlarmsMode OBJECT-TYPE
    SYNTAX DisplayString
    MAX-ACCESS read-write
    STATUS current
    DESCRIPTION
        "RTS mode (OFF,LISTEN,PUSH) for alarms file"
    ::= { rtsAlarms 1 }
    --1.3.6.1.4.1.3052.17.2.4.13.2.1

rtsAlarmsShowAnswer OBJECT-TYPE
    SYNTAX DisplayString
    MAX-ACCESS read-write
    STATUS current
    DESCRIPTION
        "Show answer string upon RTS connect for alarms file"
    ::= { rtsAlarms 2 }
    --1.3.6.1.4.1.3052.17.2.4.13.2.2

rtsAlarmsReqXON OBJECT-TYPE
    SYNTAX DisplayString
    MAX-ACCESS read-write
    STATUS current
    DESCRIPTION
        "ON/OFF require XON to start flow for alarms file"
    ::= { rtsAlarms 3 }
    --1.3.6.1.4.1.3052.17.2.4.13.2.3

rtsAlarmsTimeout OBJECT-TYPE
    SYNTAX Integer32
    MAX-ACCESS read-write
    STATUS current
    DESCRIPTION
        "Idle connection close timer (0 means no timeout) for alarms
        file"
    ::= { rtsAlarms 4 }
    --1.3.6.1.4.1.3052.17.2.4.13.2.4

rtsAlarmsEmptyClose OBJECT-TYPE
    SYNTAX DisplayString
    MAX-ACCESS read-write
    STATUS current
    DESCRIPTION
        "ON/OFF close the socket when this file is empty for alarms
        file"
    ::= { rtsAlarms 5 }
    --1.3.6.1.4.1.3052.17.2.4.13.2.5

rtsAlarmsPushHost OBJECT-TYPE
    SYNTAX DisplayString
    MAX-ACCESS read-write
    STATUS current
    DESCRIPTION
        "Host to which alarms file should be pushed via RTS"
    ::= { rtsAlarms 6 }
    --1.3.6.1.4.1.3052.17.2.4.13.2.6

rtsAlarmsPushPort OBJECT-TYPE
    SYNTAX Integer32
    MAX-ACCESS read-write
    STATUS current
    DESCRIPTION
        "TCP port to which alarms file should be pushed via RTS"
    ::= { rtsAlarms 7 }
    --1.3.6.1.4.1.3052.17.2.4.13.2.7

rtsAlarmsPushRetryTimer OBJECT-TYPE
    SYNTAX Integer32
    MAX-ACCESS read-write
    STATUS current
    DESCRIPTION
        "Retry timer (seconds) for retrying failed RTS push connect
        attempts"
    ::= { rtsAlarms 8 }
    --1.3.6.1.4.1.3052.17.2.4.13.2.8

-- Traps

trapIncludeDateTime OBJECT-TYPE
    SYNTAX DisplayString
    MAX-ACCESS read-write
    STATUS current
    DESCRIPTION
        "ON/OFF include date and time in stock trap message"
    ::= { trapInclude 1 }
    --1.3.6.1.4.1.3052.17.2.4.14.1.1

trapIncludeSiteName OBJECT-TYPE
    SYNTAX DisplayString
    MAX-ACCESS read-write
    STATUS current
    DESCRIPTION
        "ON/OFF include site name in stock trap message"
    ::= { trapInclude 2 }
    --1.3.6.1.4.1.3052.17.2.4.14.1.2

trapIncludeSensorID OBJECT-TYPE
    SYNTAX DisplayString
    MAX-ACCESS read-write
    STATUS current
    DESCRIPTION
        "ON/OFF include sensor ID in stock trap message"
    ::= { trapInclude 3 }
    --1.3.6.1.4.1.3052.17.2.4.14.1.3

trapIncludeUDName OBJECT-TYPE
    SYNTAX DisplayString
    MAX-ACCESS read-write
    STATUS current
    DESCRIPTION
        "ON/OFF include user defined name in stock trap message"
    ::= { trapInclude 4 }
    --1.3.6.1.4.1.3052.17.2.4.14.1.4

trapIncludeUDState OBJECT-TYPE
    SYNTAX DisplayString
    MAX-ACCESS read-write
    STATUS current
    DESCRIPTION
        "ON/OFF include user defined state in stock trap message"
    ::= { trapInclude 5 }
    --1.3.6.1.4.1.3052.17.2.4.14.1.5

trapIncludeSourceAddress OBJECT-TYPE
    SYNTAX IpAddress
    MAX-ACCESS read-write
    STATUS current
    DESCRIPTION
        "ON/OFF include source IP address in stock trap message"
    ::= { trapInclude 6 }
    --1.3.6.1.4.1.3052.17.2.4.14.1.6

trapAuthFailEnable OBJECT-TYPE
    SYNTAX DisplayString
    MAX-ACCESS read-write
    STATUS current
    DESCRIPTION
        "ON/OFF enable trap sent upon SNMP authentication failure"
    ::= { trap 2 }
    --1.3.6.1.4.1.3052.17.2.4.14.2


-- Wireless


wirelessMode OBJECT-TYPE
    SYNTAX DisplayString
    MAX-ACCESS read-write
    STATUS current
    DESCRIPTION
        "Wireless mode (OFF,PERMANENT-EDGE)"
    ::= { wireless 1 }
    --1.3.6.1.4.1.3052.17.2.4.16.1

wirelessAPN OBJECT-TYPE
    SYNTAX DisplayString
    MAX-ACCESS read-write
    STATUS current
    DESCRIPTION
        "Wireless access point name"
    ::= { wireless 2 }
    --1.3.6.1.4.1.3052.17.2.4.16.2

wirelessIdleTimeout OBJECT-TYPE
    SYNTAX Integer32 (3..255)
    MAX-ACCESS read-write
    STATUS current
    DESCRIPTION
        "Wireless idle timeout"
    ::= { wireless 3 }
    --1.3.6.1.4.1.3052.17.2.4.16.3

wirelessPIN OBJECT-TYPE
    SYNTAX DisplayString
    MAX-ACCESS read-write
    STATUS current
    DESCRIPTION
        "Wireless modem SIM PIN"
    ::= { wireless 5 }
    --1.3.6.1.4.1.3052.17.2.4.16.5

wirelessDRE OBJECT-TYPE
    SYNTAX DisplayString
    MAX-ACCESS read-write
    STATUS current
    DESCRIPTION
        "Default route enable for wireless network interface.
         When this is ON, the wireless link, if up, becomes
         the default route, overriding the default route setting
         (defaultRouter object).  When OFF, the default route
         setting controls the default route and the wireless link
         does not become the default route."
    ::= { wireless 9 }
    --1.3.6.1.4.1.3052.17.2.4.16.9

-- Email


emailServer OBJECT-TYPE
    SYNTAX DisplayString
    MAX-ACCESS read-write
    STATUS current
    DESCRIPTION
        "SMTP server to which the unit sends email"
    ::= { email 1 }
    --1.3.6.1.4.1.3052.17.2.4.17.1

emailDomain OBJECT-TYPE
    SYNTAX DisplayString
    MAX-ACCESS read-write
    STATUS current
    DESCRIPTION
        "Domain to use in recipient address"
    ::= { email 2 }
    --1.3.6.1.4.1.3052.17.2.4.17.2

emailAuthEnable OBJECT-TYPE
    SYNTAX DisplayString
    MAX-ACCESS read-write
    STATUS current
    DESCRIPTION
        "ON/OFF enable SMTP authentication"
    ::= { email 3 }
    --1.3.6.1.4.1.3052.17.2.4.17.3

-- Advanced network config

arpFilter OBJECT-TYPE
    SYNTAX Integer32
    MAX-ACCESS read-write
    STATUS current
    DESCRIPTION
        "ARP filter code"
    ::= { netAdvanced 1 }
    --1.3.6.1.4.1.3052.17.2.4.18.1


-- Web interface

webEnable OBJECT-TYPE
    SYNTAX DisplayString
    MAX-ACCESS read-write
    STATUS current
    DESCRIPTION
        "ON/OFF for the web interface"
    ::= { web 1 }
    --1.3.6.1.4.1.3052.17.2.4.19.1

webPort OBJECT-TYPE
    SYNTAX Integer32
    MAX-ACCESS read-write
    STATUS current
    DESCRIPTION
        "TCP port on which web interface listens"
    ::= { web 2 }
    --1.3.6.1.4.1.3052.17.2.4.19.2

webTimeout OBJECT-TYPE
    SYNTAX Integer32
    MAX-ACCESS read-write
    STATUS current
    DESCRIPTION
        "Web interface session timeout (seconds)"
    ::= { web 3 }
    --1.3.6.1.4.1.3052.17.2.4.19.3


--***************************************************************************************
--Time Section  2.8
--***************************************************************************************

clock OBJECT-TYPE
    SYNTAX DisplayString
    MAX-ACCESS read-write
    STATUS current
    DESCRIPTION
        "Text string for date and time;
        e.g. 'SUN 01/02/98 12:34:27'.  When setting
        this object, only the date and time are
        required; the unit will ignore a specified
        day of week because it is calculated from
        the date and time.  When this object is included
        in a notification as a varbind, it represents
        the time that the triggering event occurred."
    ::= { time 1 }
    --1.3.6.1.4.1.3052.17.2.8.1

--***************************************************************************************
--Console Section  2.10
--***************************************************************************************


consoleDuplex OBJECT-TYPE
    SYNTAX DisplayString
    MAX-ACCESS read-write
    STATUS current
    DESCRIPTION
        "ON/OFF characters echoed on telnet command session"
    ::= { console 1 }
    --1.3.6.1.4.1.3052.17.2.10.1

consoleTimeout OBJECT-TYPE
    SYNTAX Integer32
    MAX-ACCESS read-write
    STATUS current
    DESCRIPTION
        "Minutes of inactivity after which telnet command session is terminated"
    ::= { console 2 }
    --1.3.6.1.4.1.3052.17.2.10.2

consoleConfirm OBJECT-TYPE
    SYNTAX DisplayString
    MAX-ACCESS read-write
    STATUS current
    DESCRIPTION
        "ON/OFF Prompt to confirm certain actions"
    ::= { console 7 }
    --1.3.6.1.4.1.3052.17.2.10.7

--***************************************************************************************
--Core Security Section 2.11.1
--***************************************************************************************

scShowPasswordPrompt OBJECT-TYPE
    SYNTAX DisplayString
    MAX-ACCESS read-write
    STATUS current
    DESCRIPTION
        "ON/OFF show password prompt upon login"
    ::= { secCore 1 }
    --1.3.6.1.4.1.3052.17.2.11.1.1

scConsoleLoginRequired  OBJECT-TYPE
    SYNTAX DisplayString
    MAX-ACCESS read-write
    STATUS current
    DESCRIPTION
        "ON/OFF login required upon connecting via console"
    ::= { secCore 2 }
    --1.3.6.1.4.1.3052.17.2.11.1.2

scModemLoginRequired OBJECT-TYPE
    SYNTAX DisplayString
    MAX-ACCESS read-write
    STATUS current
    DESCRIPTION
        "ON/OFF login required upon connecting via modem"
    ::= { secCore 3 }
    --1.3.6.1.4.1.3052.17.2.11.1.3

scTelnetLoginRequired OBJECT-TYPE
    SYNTAX DisplayString
    MAX-ACCESS read-write
    STATUS current
    DESCRIPTION
        "ON/OFF login required upon connecting via Telnet"
    ::= { secCore 4 }
    --1.3.6.1.4.1.3052.17.2.11.1.4

scTelnetPTLoginRequired OBJECT-TYPE
    SYNTAX DisplayString
    MAX-ACCESS read-write
    STATUS current
    DESCRIPTION
        "ON/OFF login required upon connecting via Telnet to pass-
        through ports (TCP ports 210x)"
    ::= { secCore 5 }
    --1.3.6.1.4.1.3052.17.2.11.1.5

scRTSLoginRequired OBJECT-TYPE
    SYNTAX DisplayString
    MAX-ACCESS read-write
    STATUS current
    DESCRIPTION
        "ON/OFF login required upon connecting to RTS (TCP ports 220x)"
    ::= { secCore 6 }
    --1.3.6.1.4.1.3052.17.2.11.1.6

scAuthMode OBJECT-TYPE
    SYNTAX DisplayString
    MAX-ACCESS read-write
    STATUS current
    DESCRIPTION
        "Authentication mode (USERNAME/PW,PW/USERNAME,PASSWORD ONLY)"
    ::= { secCore 7 }
    --1.3.6.1.4.1.3052.17.2.11.1.7

scRightsGroup OBJECT-TYPE
    SYNTAX DisplayString
    MAX-ACCESS read-write
    STATUS current
    DESCRIPTION
        "The set of aliases used for the 8 available rights levels"
    ::= { secCore 8 }
    --1.3.6.1.4.1.3052.17.2.11.1.8

scSecret OBJECT-TYPE
    SYNTAX DisplayString
    MAX-ACCESS read-write
    STATUS current
    DESCRIPTION
        "Shared secret for challenges"
    ::= { secCore 9 }
    --1.3.6.1.4.1.3052.17.2.11.1.9



--***************************************************************************************
--User Security Section 2.11.2
--***************************************************************************************


secUserTable OBJECT-TYPE
    SYNTAX SEQUENCE OF SecUserConfig
    MAX-ACCESS not-accessible
    STATUS current
    DESCRIPTION
        "Table of users"
    ::= { unitSecurity 2 }
    --1.3.6.1.4.1.3052.17.2.11.2

secUserEntry OBJECT-TYPE
    SYNTAX SecUserConfig
    MAX-ACCESS not-accessible
    STATUS current
    DESCRIPTION
        "Entry for table of users"
    INDEX { secUserIndex }
    ::= { secUserTable 1 }
    --1.3.6.1.4.1.3052.17.2.11.2.1

secUserIndex OBJECT-TYPE
    SYNTAX Integer32 (1..12)
    MAX-ACCESS read-only
    STATUS current
    DESCRIPTION
        "Index for table of users"
    ::= { secUserEntry 1 }
    --1.3.6.1.4.1.3052.17.2.11.2.1.1

secUserEnable OBJECT-TYPE
    SYNTAX DisplayString
    MAX-ACCESS read-write
    STATUS current
    DESCRIPTION
        "ON/OFF enable user"
    ::= { secUserEntry 2 }
    --1.3.6.1.4.1.3052.17.2.11.2.1.2

secUserConnectVia OBJECT-TYPE
    SYNTAX DisplayString
    MAX-ACCESS read-write
    STATUS current
    DESCRIPTION
        "Methods by which user is allowed to connect:
        L=local (console)
        T=Telnet
        F=FTP
        R=RTS
        Ss=SSH
        W=Web
        "
    ::= { secUserEntry 5 }
    --1.3.6.1.4.1.3052.17.2.11.2.1.5

secUserLoginTo OBJECT-TYPE
    SYNTAX DisplayString
    MAX-ACCESS read-write
    STATUS current
    DESCRIPTION
        "The function presented to the user upon login (COMMAND,
        PASSTHROUGH,MENU)"
    ::= { secUserEntry 6 }
    --1.3.6.1.4.1.3052.17.2.11.2.1.6

secUserAccessFile OBJECT-TYPE
    SYNTAX DisplayString
    MAX-ACCESS read-write
    STATUS current
    DESCRIPTION
        "The default access file associated with the user"
    ::= { secUserEntry 7 }
    --1.3.6.1.4.1.3052.17.2.11.2.1.7

secUserPTEscapeTo OBJECT-TYPE
    SYNTAX DisplayString
    MAX-ACCESS read-write
    STATUS current
    DESCRIPTION
        "The function presented to the user upon escaping pass-
        through: currently only MENU"
    ::= { secUserEntry 9 }
    --1.3.6.1.4.1.3052.17.2.11.2.1.9

secUserPPPType OBJECT-TYPE
    SYNTAX DisplayString
    MAX-ACCESS read-write
    STATUS current
    DESCRIPTION
        "The kind of PPP access allowed to this user cannot connect
        via PPP (NONE), can connect but only to the unit (LOCAL), or
        can connect and route to Ethernet (ROUTING)"
    ::= { secUserEntry 10 }
    --1.3.6.1.4.1.3052.17.2.11.2.1.10

secUserRights OBJECT-TYPE
    SYNTAX DisplayString
    MAX-ACCESS read-write
    STATUS current
    DESCRIPTION
        "The rights level granted to this user"
    ::= { secUserEntry 11 }
    --1.3.6.1.4.1.3052.17.2.11.2.1.11

secUserEventsReadAccess OBJECT-TYPE
    SYNTAX DisplayString
    MAX-ACCESS read-write
    STATUS current
    DESCRIPTION
        "DENY/ALLOW user to read the events/alarms file"
    ::= { secUserEntry 13 }
    --1.3.6.1.4.1.3052.17.2.11.2.1.13

secUserAuditReadAccess OBJECT-TYPE
    SYNTAX DisplayString
    MAX-ACCESS read-write
    STATUS current
    DESCRIPTION
        "DENY/ALLOW user to read the audit log"
    ::= { secUserEntry 14 }
    --1.3.6.1.4.1.3052.17.2.11.2.1.14

secUserEventsWriteAccess OBJECT-TYPE
    SYNTAX DisplayString
    MAX-ACCESS read-write
    STATUS current
    DESCRIPTION
        "DENY/ALLOW user to delete the events file"
    ::= { secUserEntry 16 }
    --1.3.6.1.4.1.3052.17.2.11.2.1.16

secUserAuditWriteAccess OBJECT-TYPE
    SYNTAX DisplayString
    MAX-ACCESS read-write
    STATUS current
    DESCRIPTION
        "DENY/ALLOW user to write to the audit log"
    ::= { secUserEntry 17 }
    --1.3.6.1.4.1.3052.17.2.11.2.1.17

secUserExpiration OBJECT-TYPE
    SYNTAX DisplayString
    MAX-ACCESS read-write
    STATUS current
    DESCRIPTION
        "Expiration date/time of this user"
    ::= { secUserEntry 18 }
    --1.3.6.1.4.1.3052.17.2.11.2.1.18

secUserCallbackNumber1 OBJECT-TYPE
    SYNTAX DisplayString
    MAX-ACCESS read-write
    STATUS current
    DESCRIPTION
        "Number slot 1 the unit calls for dialback"
    ::= { secUserEntry 19 }
    --1.3.6.1.4.1.3052.17.2.11.2.1.19

secUserCallbackNumber2 OBJECT-TYPE
    SYNTAX DisplayString
    MAX-ACCESS read-write
    STATUS current
    DESCRIPTION
        "Number slot 2 the unit calls for dialback"
    ::= { secUserEntry 20 }
    --1.3.6.1.4.1.3052.17.2.11.2.1.20

secUserCallbackNumber3 OBJECT-TYPE
    SYNTAX DisplayString
    MAX-ACCESS read-write
    STATUS current
    DESCRIPTION
        "Number slot 3 the unit calls for dialback"
    ::= { secUserEntry 21 }
    --1.3.6.1.4.1.3052.17.2.11.2.1.21

secUserChallengeTelnetMode OBJECT-TYPE
    SYNTAX DisplayString
    MAX-ACCESS read-write
    STATUS current
    DESCRIPTION
        "Telnet challenge mode: when user logs in via telnet, unit
        allows access (OFF), presents a challenge (CHALLENGE), or
        unit sends a one-time-password (SEND PASSWORD) to a
        destination configured by secUserChallengeTelnetSendTo"
    ::= { secUserEntry 22 }
    --1.3.6.1.4.1.3052.17.2.11.2.1.22

secUserChallengeModemMode OBJECT-TYPE
    SYNTAX DisplayString
    MAX-ACCESS read-write
    STATUS current
    DESCRIPTION
        "Modem challenge mode: when user logs in via modem, unit
        allows access (OFF), presents a challenge (CHALLENGE), sends
        a one-time-password (SEND PASSWORD) to a destination
        configured by secUserChallengeTelnetSendTo, or dials a
        number (CALLBACK) configured with secUserCallbackNumberx"
    ::= { secUserEntry 23 }
    --1.3.6.1.4.1.3052.17.2.11.2.1.23

secUserChallengeConsoleMode OBJECT-TYPE
    SYNTAX DisplayString
    MAX-ACCESS read-write
    STATUS current
    DESCRIPTION
        "Console challenge mode: when user logs in via console, unit
        allows access (OFF), or presents a challenge (CHALLENGE)"
    ::= { secUserEntry 24 }
    --1.3.6.1.4.1.3052.17.2.11.2.1.24

secUserChallengeTelnetSendTo OBJECT-TYPE
    SYNTAX DisplayString
    MAX-ACCESS read-write
    STATUS current
    DESCRIPTION
        "Email action used as the destination address for one-time-
        password when a user logs in with a challenge mode of
        SEND PASSWORD"
    ::= { secUserEntry 25 }
    --1.3.6.1.4.1.3052.17.2.11.2.1.25

secUserChallengeModemSendTo OBJECT-TYPE
    SYNTAX DisplayString
    MAX-ACCESS read-write
    STATUS current
    DESCRIPTION
        "Modem action used as the destination phone number for one-
        time-password when a user logs in with a challenge mode of
        SEND PASSWORD"
    ::= { secUserEntry 26 }
    --1.3.6.1.4.1.3052.17.2.11.2.1.26

secUserChallengeExpiration OBJECT-TYPE
    SYNTAX Integer32 (0..180)
    MAX-ACCESS read-write
    STATUS current
    DESCRIPTION
        "Time (in minutes) after which a one-time-password is sent
        that it can be used to log in"
    ::= { secUserEntry 27 }
    --1.3.6.1.4.1.3052.17.2.11.2.1.27


--***************************************************************************************
--Factory Security Section 2.11.3
--***************************************************************************************

sfEnable OBJECT-TYPE
    SYNTAX DisplayString
    MAX-ACCESS read-write
    STATUS current
    DESCRIPTION
        "ON/OFF enable factory access"
    ::= { secFactory 1 }
    --1.3.6.1.4.1.3052.17.2.11.3.1

sfSecret OBJECT-TYPE
    SYNTAX DisplayString
    MAX-ACCESS read-write
    STATUS current
    DESCRIPTION
        "Secret used for factory access"
    ::= { secFactory 2 }
    --1.3.6.1.4.1.3052.17.2.11.3.2


--***************************************************************************************
--Event Section   2.12
--***************************************************************************************

--***************************************************************************************
--Event Core Section   2.12.1
--***************************************************************************************


evClassNameTable OBJECT-TYPE
    SYNTAX SEQUENCE OF EventClassConfig
    MAX-ACCESS not-accessible
    STATUS current
    DESCRIPTION
        "Table of classes"
    ::= { evCore 1 }
    --1.3.6.1.4.1.3052.17.2.12.1.1

evClassNameEntry OBJECT-TYPE
    SYNTAX EventClassConfig
    MAX-ACCESS not-accessible
    STATUS current
    DESCRIPTION
        "Entry for table of classes"
    INDEX { evClassNameIndex }
    ::= { evClassNameTable 1 }
    --1.3.6.1.4.1.3052.17.2.12.1.1.1

evClassNameIndex OBJECT-TYPE
    SYNTAX Integer32 (1..12)
    MAX-ACCESS read-only
    STATUS current
    DESCRIPTION
        "Index for table of classes"
    ::= { evClassNameEntry 1 }
    --1.3.6.1.4.1.3052.17.2.12.1.1.1.1

evClassName OBJECT-TYPE
    SYNTAX DisplayString
    MAX-ACCESS read-write
    STATUS current
    DESCRIPTION
        "Class name for this slot"
    ::= { evClassNameEntry 2 }
    --1.3.6.1.4.1.3052.17.2.12.1.1.1.2

evReminderInterval OBJECT-TYPE
    SYNTAX Integer32 (0..65535)
    MAX-ACCESS read-write
    STATUS current
    DESCRIPTION
        "Interval (minutes) between EventSensor reminder events"
    ::= { evCore 2 }
    --1.3.6.1.4.1.3052.17.2.12.1.2

evLogEnable OBJECT-TYPE
    SYNTAX DisplayString
    MAX-ACCESS read-write
    STATUS current
    DESCRIPTION
        "ON/OFF enable event log"
    ::= { evLog 1 }
    --1.3.6.1.4.1.3052.17.2.12.1.3.1

evLogStoreAlarm OBJECT-TYPE
    SYNTAX DisplayString
    MAX-ACCESS read-write
    STATUS current
    DESCRIPTION
        "ON/OFF store data alarms in event log"
    ::= { evLog 2 }
    --1.3.6.1.4.1.3052.17.2.12.1.3.2

evLogMaxSize OBJECT-TYPE
    SYNTAX Integer32
    MAX-ACCESS read-write
    STATUS current
    DESCRIPTION
        "max size (in KB) of event log"
    ::= { evLog 3 }
    --1.3.6.1.4.1.3052.17.2.12.1.3.3

evLogStoreSensor OBJECT-TYPE
    SYNTAX DisplayString
    MAX-ACCESS read-write
    STATUS current
    DESCRIPTION
        "ON/OFF store EventSensor events in event log"
    ::= { evLog 4 }
    --1.3.6.1.4.1.3052.17.2.12.1.3.4

evLogTimeStampAlarms OBJECT-TYPE
    SYNTAX DisplayString
    MAX-ACCESS read-write
    STATUS current
    DESCRIPTION
        "ON/OFF put timestamps on event log entries"
    ::= { evLog 5 }
    --1.3.6.1.4.1.3052.17.2.12.1.3.5

evLogPrependName OBJECT-TYPE
    SYNTAX DisplayString
    MAX-ACCESS read-write
    STATUS current
    DESCRIPTION
        "ON/OFF prepend data event name to data alarm records in event
        log"
    ::= { evLog 6 }
    --1.3.6.1.4.1.3052.17.2.12.1.3.6


evMgmtReprocess OBJECT-TYPE
    SYNTAX DisplayString
    MAX-ACCESS read-write
    STATUS current
    DESCRIPTION
        "Number of sensors that have generated events since reset.
        Write this to reprocess each sensor's last generated event
        since reset.  The value to write determines what kind of
        events should be reprocessed:
                'all': all sensor events
                 'cc': cc events
        'temperature': temperature events
           'humidity': humidity events
             'analog': analog input events
               'fuel': fuel sensor events
               'acpm': AC power monitor events
            'battery': battery monitor events"
    ::= { evMgmt 3 }
    --1.3.6.1.4.1.3052.17.2.12.1.4.3


--***************************************************************************************
--Scheduled Event 1 Section 2.12.5
--***************************************************************************************

evSched1Enable OBJECT-TYPE
    SYNTAX DisplayString
    MAX-ACCESS read-write
    STATUS current
    DESCRIPTION
        "ON/OFF enable this scheduled event"
    ::= { evSched1 1 }
    --1.3.6.1.4.1.3052.17.2.12.5.1

evSched1Actions OBJECT-TYPE
    SYNTAX DisplayString
    MAX-ACCESS read-write
    STATUS current
    DESCRIPTION
        "Actions for this scheduled event"
    ::= { evSched1 2 }
    --1.3.6.1.4.1.3052.17.2.12.5.2

evSched1Message OBJECT-TYPE
    SYNTAX DisplayString
    MAX-ACCESS read-write
    STATUS current
    DESCRIPTION
        "Message for this scheduled event"
    ::= { evSched1 3 }
    --1.3.6.1.4.1.3052.17.2.12.5.3

evSched1TrapNum OBJECT-TYPE
    SYNTAX Integer32
    MAX-ACCESS read-write
    STATUS current
    DESCRIPTION
        "Trap number for this scheduled event"
    ::= { evSched1 4 }
    --1.3.6.1.4.1.3052.17.2.12.5.4

evSched1Class OBJECT-TYPE
    SYNTAX DisplayString
    MAX-ACCESS read-write
    STATUS current
    DESCRIPTION
        "Class for this scheduled event"
    ::= { evSched1 5 }
    --1.3.6.1.4.1.3052.17.2.12.5.5

evSched1Sunday OBJECT-TYPE
    SYNTAX DisplayString
    MAX-ACCESS read-write
    STATUS current
    DESCRIPTION
        "Time on Sunday (HH:MM) when this scheduled event triggers"
    ::= { evSched1 6 }
    --1.3.6.1.4.1.3052.17.2.12.5.6

evSched1Monday OBJECT-TYPE
    SYNTAX DisplayString
    MAX-ACCESS read-write
    STATUS current
    DESCRIPTION
        "Time on Monday (HH:MM) when this scheduled event triggers"
    ::= { evSched1 7 }
    --1.3.6.1.4.1.3052.17.2.12.5.7

evSched1Tuesday OBJECT-TYPE
    SYNTAX DisplayString
    MAX-ACCESS read-write
    STATUS current
    DESCRIPTION
        "Time on Tuesday (HH:MM) when this scheduled event triggers"
    ::= { evSched1 8 }
    --1.3.6.1.4.1.3052.17.2.12.5.8

evSched1Wednesday OBJECT-TYPE
    SYNTAX DisplayString
    MAX-ACCESS read-write
    STATUS current
    DESCRIPTION
        "Time on Wednesday (HH:MM) when this scheduled event triggers"
    ::= { evSched1 9 }
    --1.3.6.1.4.1.3052.17.2.12.5.9

evSched1Thursday OBJECT-TYPE
    SYNTAX DisplayString
    MAX-ACCESS read-write
    STATUS current
    DESCRIPTION
        "Time on Thursday (HH:MM) when this scheduled event triggers"
    ::= { evSched1 10 }
    --1.3.6.1.4.1.3052.17.2.12.5.10

evSched1Friday OBJECT-TYPE
    SYNTAX DisplayString
    MAX-ACCESS read-write
    STATUS current
    DESCRIPTION
        "Time on Friday (HH:MM) when this scheduled event triggers"
    ::= { evSched1 11 }
    --1.3.6.1.4.1.3052.17.2.12.5.11

evSched1Saturday OBJECT-TYPE
    SYNTAX DisplayString
    MAX-ACCESS read-write
    STATUS current
    DESCRIPTION
        "Time on Saturday (HH:MM) when this scheduled event triggers"
    ::= { evSched1 12 }
    --1.3.6.1.4.1.3052.17.2.12.5.12

evSched1Exclusions OBJECT-TYPE
    SYNTAX DisplayString
    MAX-ACCESS read-write
    STATUS current
    DESCRIPTION
        "Exclusions (space-separated MM/DD-formatted dates) for this
        scheduled event"
    ::= { evSched1 13 }
    --1.3.6.1.4.1.3052.17.2.12.5.13


--***************************************************************************************
--Scheduled Event 2 Section 2.12.6
--***************************************************************************************

evSched2Enable OBJECT-TYPE
    SYNTAX DisplayString
    MAX-ACCESS read-write
    STATUS current
    DESCRIPTION
        "ON/OFF enable this scheduled event"
    ::= { evSched2 1 }
    --1.3.6.1.4.1.3052.17.2.12.6.1

evSched2Actions OBJECT-TYPE
    SYNTAX DisplayString
    MAX-ACCESS read-write
    STATUS current
    DESCRIPTION
        "Actions for this scheduled event"
    ::= { evSched2 2 }
    --1.3.6.1.4.1.3052.17.2.12.6.2

evSched2Message OBJECT-TYPE
    SYNTAX DisplayString
    MAX-ACCESS read-write
    STATUS current
    DESCRIPTION
        "Message for this scheduled event"
    ::= { evSched2 3 }
    --1.3.6.1.4.1.3052.17.2.12.6.3

evSched2TrapNum OBJECT-TYPE
    SYNTAX Integer32
    MAX-ACCESS read-write
    STATUS current
    DESCRIPTION
        "Trap number for this scheduled event"
    ::= { evSched2 4 }
    --1.3.6.1.4.1.3052.17.2.12.6.4

evSched2Class OBJECT-TYPE
    SYNTAX DisplayString
    MAX-ACCESS read-write
    STATUS current
    DESCRIPTION
        "Class for this scheduled event"
    ::= { evSched2 5 }
    --1.3.6.1.4.1.3052.17.2.12.6.5

evSched2Sunday OBJECT-TYPE
    SYNTAX DisplayString
    MAX-ACCESS read-write
    STATUS current
    DESCRIPTION
        "Time on Sunday (HH:MM) when this scheduled event triggers"
    ::= { evSched2 6 }
    --1.3.6.1.4.1.3052.17.2.12.6.6

evSched2Monday OBJECT-TYPE
    SYNTAX DisplayString
    MAX-ACCESS read-write
    STATUS current
    DESCRIPTION
        "Time on Monday (HH:MM) when this scheduled event triggers"
    ::= { evSched2 7 }
    --1.3.6.1.4.1.3052.17.2.12.6.7

evSched2Tuesday OBJECT-TYPE
    SYNTAX DisplayString
    MAX-ACCESS read-write
    STATUS current
    DESCRIPTION
        "Time on Tuesday (HH:MM) when this scheduled event triggers"
    ::= { evSched2 8 }
    --1.3.6.1.4.1.3052.17.2.12.6.8

evSched2Wednesday OBJECT-TYPE
    SYNTAX DisplayString
    MAX-ACCESS read-write
    STATUS current
    DESCRIPTION
        "Time on Wednesday (HH:MM) when this scheduled event triggers"
    ::= { evSched2 9 }
    --1.3.6.1.4.1.3052.17.2.12.6.9

evSched2Thursday OBJECT-TYPE
    SYNTAX DisplayString
    MAX-ACCESS read-write
    STATUS current
    DESCRIPTION
        "Time on Thursday (HH:MM) when this scheduled event triggers"
    ::= { evSched2 10 }
    --1.3.6.1.4.1.3052.17.2.12.6.10

evSched2Friday OBJECT-TYPE
    SYNTAX DisplayString
    MAX-ACCESS read-write
    STATUS current
    DESCRIPTION
        "Time on Friday (HH:MM) when this scheduled event triggers"
    ::= { evSched2 11 }
    --1.3.6.1.4.1.3052.17.2.12.6.11

evSched2Saturday OBJECT-TYPE
    SYNTAX DisplayString
    MAX-ACCESS read-write
    STATUS current
    DESCRIPTION
        "Time on Saturday (HH:MM) when this scheduled event triggers"
    ::= { evSched2 12 }
    --1.3.6.1.4.1.3052.17.2.12.6.12

evSched2Exclusions OBJECT-TYPE
    SYNTAX DisplayString
    MAX-ACCESS read-write
    STATUS current
    DESCRIPTION
        "Exclusions (space-separated MM/DD-formatted dates) for this
        scheduled event"
    ::= { evSched2 13 }
    --1.3.6.1.4.1.3052.17.2.12.6.13

--***************************************************************************************
--Serial Handshaking Low Section 2.12.7
--***************************************************************************************

evShskLowTable OBJECT-TYPE
    SYNTAX SEQUENCE OF SerialHandshakingLowEventConfig
    MAX-ACCESS not-accessible
    STATUS current
    DESCRIPTION
        "Table of serial handshaking low events"
    ::= { event 7 }
    --1.3.6.1.4.1.3052.17.2.12.7

evShskLowEntry OBJECT-TYPE
    SYNTAX SerialHandshakingLowEventConfig
    MAX-ACCESS not-accessible
    STATUS current
    DESCRIPTION
        "Entry for table of serial handshaking low events"
    INDEX { evShskLowIndex }
    ::= { evShskLowTable 1 }
    --1.3.6.1.4.1.3052.17.2.12.7.1

evShskLowIndex OBJECT-TYPE
    SYNTAX Integer32 (1..16)
    MAX-ACCESS read-only
    STATUS current
    DESCRIPTION
        "Index for table of serial handshaking low events"
    ::= { evShskLowEntry 1 }
    --1.3.6.1.4.1.3052.17.2.12.7.1.1

evShskLowEnable OBJECT-TYPE
    SYNTAX DisplayString
    MAX-ACCESS read-write
    STATUS current
    DESCRIPTION
        "ON/OFF: enable the serial handshaking low event for this port"
    ::= { evShskLowEntry 2 }
    --1.3.6.1.4.1.3052.17.2.12.7.1.2

evShskLowActions OBJECT-TYPE
    SYNTAX DisplayString
    MAX-ACCESS read-write
    STATUS current
    DESCRIPTION
        "Actions for the serial handshaking low event for this port"
    ::= { evShskLowEntry 3 }
    --1.3.6.1.4.1.3052.17.2.12.7.1.3

evShskLowMessage OBJECT-TYPE
    SYNTAX DisplayString
    MAX-ACCESS read-write
    STATUS current
    DESCRIPTION
        "Message for the serial handshaking low event for this port"
    ::= { evShskLowEntry 4 }
    --1.3.6.1.4.1.3052.17.2.12.7.1.4

evShskLowClass OBJECT-TYPE
    SYNTAX DisplayString
    MAX-ACCESS read-write
    STATUS current
    DESCRIPTION
        "Class for the serial handshaking low event for this port"
    ::= { evShskLowEntry 5 }
    --1.3.6.1.4.1.3052.17.2.12.7.1.5

evShskLowTrapNum OBJECT-TYPE
    SYNTAX Integer32
    MAX-ACCESS read-write
    STATUS current
    DESCRIPTION
        "Trap number for the serial handshaking low event for this port"
    ::= { evShskLowEntry 6 }
    --1.3.6.1.4.1.3052.17.2.12.7.1.6


--***************************************************************************************
--Serial Handshaking High Section 2.12.8
--***************************************************************************************

evShskHighTable OBJECT-TYPE
    SYNTAX SEQUENCE OF SerialHandshakingHighEventConfig
    MAX-ACCESS not-accessible
    STATUS current
    DESCRIPTION
        "Table of serial handshaking high events"
    ::= { event 8 }
    --1.3.6.1.4.1.3052.17.2.12.8

evShskHighEntry OBJECT-TYPE
    SYNTAX SerialHandshakingHighEventConfig
    MAX-ACCESS not-accessible
    STATUS current
    DESCRIPTION
        "Entry for table of serial handshaking high events"
    INDEX { evShskHighIndex }
    ::= { evShskHighTable 1 }
    --1.3.6.1.4.1.3052.17.2.12.8.1

evShskHighIndex OBJECT-TYPE
    SYNTAX Integer32 (1..16)
    MAX-ACCESS read-only
    STATUS current
    DESCRIPTION
        "Index for table of serial handshaking high events"
    ::= { evShskHighEntry 1 }
    --1.3.6.1.4.1.3052.17.2.12.8.1.1

evShskHighEnable OBJECT-TYPE
    SYNTAX DisplayString
    MAX-ACCESS read-write
    STATUS current
    DESCRIPTION
        "ON/OFF: enable the serial handshaking high event for this
        port"
    ::= { evShskHighEntry 2 }
    --1.3.6.1.4.1.3052.17.2.12.8.1.2

evShskHighActions OBJECT-TYPE
    SYNTAX DisplayString
    MAX-ACCESS read-write
    STATUS current
    DESCRIPTION
        "Actions for the serial handshaking high event for this port"
    ::= { evShskHighEntry 3 }
    --1.3.6.1.4.1.3052.17.2.12.8.1.3

evShskHighMessage OBJECT-TYPE
    SYNTAX DisplayString
    MAX-ACCESS read-write
    STATUS current
    DESCRIPTION
        "Message for the serial handshaking high event for this port"
    ::= { evShskHighEntry 4 }
    --1.3.6.1.4.1.3052.17.2.12.8.1.4

evShskHighClass OBJECT-TYPE
    SYNTAX DisplayString
    MAX-ACCESS read-write
    STATUS current
    DESCRIPTION
        "Class for the serial handshaking high event for this port"
    ::= { evShskHighEntry 5 }
    --1.3.6.1.4.1.3052.17.2.12.8.1.5

evShskHighTrapNum OBJECT-TYPE
    SYNTAX Integer32
    MAX-ACCESS read-write
    STATUS current
    DESCRIPTION
        "Trap number for the serial handshaking high event for this
        port"
    ::= { evShskHighEntry 6 }
    --1.3.6.1.4.1.3052.17.2.12.8.1.6


--***************************************************************************************
--No Sensor Event Section 2.12.9
--***************************************************************************************

evNoSensorTimeout OBJECT-TYPE
    SYNTAX Integer32
    MAX-ACCESS read-write
    STATUS current
    DESCRIPTION
        "Timeout (seconds) after which an EventSensor becomes
        unresponsive that this event is triggered"
    ::= { evNoSensor 1 }
    --1.3.6.1.4.1.3052.17.2.12.9.1

evNoSensorActions OBJECT-TYPE
    SYNTAX DisplayString
    MAX-ACCESS read-write
    STATUS current
    DESCRIPTION
        "Actions for no sensor event"
    ::= { evNoSensor 2 }
    --1.3.6.1.4.1.3052.17.2.12.9.2

evNoSensorTrapNum OBJECT-TYPE
    SYNTAX Integer32
    MAX-ACCESS read-write
    STATUS current
    DESCRIPTION
        "Trap number for no sensor event"
    ::= { evNoSensor 3 }
    --1.3.6.1.4.1.3052.17.2.12.9.3

evNoSensorClass OBJECT-TYPE
    SYNTAX DisplayString
    MAX-ACCESS read-write
    STATUS current
    DESCRIPTION
        "Class for no sensor event"
    ::= { evNoSensor 4 }
    --1.3.6.1.4.1.3052.17.2.12.9.4



--***************************************************************************************
--Fuel Sensor Config Section       2.12.11
--***************************************************************************************


fuelSensorGeneralTable OBJECT-TYPE
    SYNTAX SEQUENCE OF FuelSensorConfigGeneral
    MAX-ACCESS not-accessible
    STATUS current
    DESCRIPTION
        "This table organizes general fuel sensor attributes."
    ::= { fuelSensor 1 }
    --1.3.6.1.4.1.3052.17.2.12.11.1

fsGenEntry OBJECT-TYPE
    SYNTAX FuelSensorConfigGeneral
    MAX-ACCESS not-accessible
    STATUS current
    DESCRIPTION
        "Entry for fuel sensor general config table."
    INDEX { fsGenIndex }
    ::= { fuelSensorGeneralTable 1 }
    --1.3.6.1.4.1.3052.17.2.12.11.1.1

fsGenIndex OBJECT-TYPE
    SYNTAX Integer32 (1..3)
    MAX-ACCESS read-only
    STATUS current
    DESCRIPTION
        "Which fuel sensor in the fuel sensor general config table."
    ::= { fsGenEntry 1 }
    --1.3.6.1.4.1.3052.17.2.12.11.1.1.1

fsGenName OBJECT-TYPE
    SYNTAX DisplayString
    MAX-ACCESS read-write
    STATUS current
    DESCRIPTION
        "Fuel sensor name."
    ::= { fsGenEntry 2 }
    --1.3.6.1.4.1.3052.17.2.12.11.1.1.2

fsGenSensorType OBJECT-TYPE
    SYNTAX DisplayString
    MAX-ACCESS read-write
    STATUS current
    DESCRIPTION
        "Type of fuel sensor in use; NONE disables the fuel sensor."
    ::= { fsGenEntry 3 }
    --1.3.6.1.4.1.3052.17.2.12.11.1.1.3

fsGenDistanceUnit OBJECT-TYPE
    SYNTAX DisplayString
    MAX-ACCESS read-write
    STATUS current
    DESCRIPTION
        "Distance units in use when setting and indicating tank dimensions."
    ::= { fsGenEntry 4 }
    --1.3.6.1.4.1.3052.17.2.12.11.1.1.4

fsGenRawValueTop OBJECT-TYPE
    SYNTAX Integer32
    MAX-ACCESS read-write
    STATUS current
    DESCRIPTION
        "Analog input reading corresponding to the SENSOR FULL point."
    ::= { fsGenEntry 5 }
    --1.3.6.1.4.1.3052.17.2.12.11.1.1.5

fsGenTopOffset OBJECT-TYPE
    SYNTAX DisplayString
    MAX-ACCESS read-write
    STATUS current
    DESCRIPTION
        "Distance, in the specified distance unit, between the SENSOR FULL
        point and the TANK FULL point.  The value is positive if the
        SENSOR FULL point is above the TANK FULL point, and negative if it is
        below."
    ::= { fsGenEntry 6 }
    --1.3.6.1.4.1.3052.17.2.12.11.1.1.6

fsGenRawValueBottom OBJECT-TYPE
    SYNTAX Integer32
    MAX-ACCESS read-write
    STATUS current
    DESCRIPTION
        "Analog input reading corresponding to the minimum fluid height
        measurable by the fuel sensor."
    ::= { fsGenEntry 7 }
    --1.3.6.1.4.1.3052.17.2.12.11.1.1.7

fsGenBottomOffset OBJECT-TYPE
    SYNTAX DisplayString
    MAX-ACCESS read-write
    STATUS current
    DESCRIPTION
        "Distance, in the specified distance unit, between the SENSOR EMPTY
        point and the TANK EMPTY point.  The value is positive if the
        SENSOR EMPTY point is above the TANK EMPTY point, and negative if it
        is below."
    ::= { fsGenEntry 8 }
    --1.3.6.1.4.1.3052.17.2.12.11.1.1.8

fsGenInputES OBJECT-TYPE
    SYNTAX Integer32 (1..200)
    MAX-ACCESS read-write
    STATUS current
    DESCRIPTION
        "Which eventsensor contains the analog input associated with this fuel
        sensor. Allowed values are 200 (for internal ES), or 1-16."
    ::= { fsGenEntry 9 }
    --1.3.6.1.4.1.3052.17.2.12.11.1.1.9

fsGenInputPoint OBJECT-TYPE
    SYNTAX Integer32 (1..16)
    MAX-ACCESS read-write
    STATUS current
    DESCRIPTION
        "Which analog input point, on the specified eventsensor, that is
        associated with the fuel sensor."
    ::= { fsGenEntry 10 }
    --1.3.6.1.4.1.3052.17.2.12.11.1.1.10

fsGenFilterAveraging OBJECT-TYPE
    SYNTAX Integer32
    MAX-ACCESS read-write
    STATUS current
    DESCRIPTION
        "Fuel sensor filter averaging factor."
    ::= { fsGenEntry 11 }
    --1.3.6.1.4.1.3052.17.2.12.11.1.1.11

fsGenSysrepEnable OBJECT-TYPE
    SYNTAX DisplayString
    MAX-ACCESS read-write
    STATUS current
    DESCRIPTION
        "Fuel sensor System Reporting enable."
    ::= { fsGenEntry 12 }
    --1.3.6.1.4.1.3052.17.2.12.11.1.1.12

fsGenSysrepThreshold OBJECT-TYPE
    SYNTAX DisplayString
    MAX-ACCESS read-write
    STATUS current
    DESCRIPTION
        "Fuel sensor System Reporting threshold (floating point value)."
    ::= { fsGenEntry 13 }
    --1.3.6.1.4.1.3052.17.2.12.11.1.1.13

fsGenSysrepLimit OBJECT-TYPE
    SYNTAX Integer32
    MAX-ACCESS read-write
    STATUS current
    DESCRIPTION
        "Fuel sensor System Reporting limit."
    ::= { fsGenEntry 14 }
    --1.3.6.1.4.1.3052.17.2.12.11.1.1.14

fsGenSysrepPackage OBJECT-TYPE
    SYNTAX Integer32 (0..10)
    MAX-ACCESS read-write
    STATUS current
    DESCRIPTION
        "Fuel sensor System Reporting package number."
    ::= { fsGenEntry 15 }
    --1.3.6.1.4.1.3052.17.2.12.11.1.1.15

fsGenSysrepType OBJECT-TYPE
    SYNTAX DisplayString
    MAX-ACCESS read-write
    STATUS current
    DESCRIPTION
        "Fuel sensor ASM profile type."
    ::= { fsGenEntry 16 }
    --1.3.6.1.4.1.3052.17.2.12.11.1.1.16


fuelSensorTankTable OBJECT-TYPE
    SYNTAX SEQUENCE OF FuelSensorConfigTank
    MAX-ACCESS not-accessible
    STATUS current
    DESCRIPTION
        "This table organizes tank-specific fuel sensor attributes."
    ::= { fuelSensor 2 }
    --1.3.6.1.4.1.3052.17.2.12.11.2

fsTankEntry OBJECT-TYPE
    SYNTAX FuelSensorConfigTank
    MAX-ACCESS not-accessible
    STATUS current
    DESCRIPTION
        "Entry for fuel sensor tank config table."
    INDEX { fsTankIndex }
    ::= { fuelSensorTankTable 1 }
    --1.3.6.1.4.1.3052.17.2.12.11.2.1

fsTankIndex OBJECT-TYPE
    SYNTAX Integer32 (1..3)
    MAX-ACCESS read-only
    STATUS current
    DESCRIPTION
        "Which fuel sensor in the fuel sensor tank config table."
    ::= { fsTankEntry 1 }
    --1.3.6.1.4.1.3052.17.2.12.11.2.1.1

fsTankHeight OBJECT-TYPE
    SYNTAX DisplayString
    MAX-ACCESS read-write
    STATUS current
    DESCRIPTION
        "Height of the tank, from the TANK EMPTY point to the TANK FULL point,
        in the specified distance unit (i.e. TANK HEIGHT).  This is a
        floating point value."
    ::= { fsTankEntry 2 }
    --1.3.6.1.4.1.3052.17.2.12.11.2.1.2

fsTankDimA OBJECT-TYPE
    SYNTAX DisplayString
    MAX-ACCESS read-write
    STATUS current
    DESCRIPTION
        "Tank dimension measurement A for certain tank profiles. For
        HORIZ OVAL, this is the length of the straight section.  This is a
        floating point value."
    ::= { fsTankEntry 3 }
    --1.3.6.1.4.1.3052.17.2.12.11.2.1.3

fsTankDimB OBJECT-TYPE
    SYNTAX DisplayString
    MAX-ACCESS read-write
    STATUS current
    DESCRIPTION
        "Tank dimension measurement B for certain tank profiles. For
        HORIZ OVAL, this is the radius of the curved section.  This is a
        floating point value."
    ::= { fsTankEntry 4 }
    --1.3.6.1.4.1.3052.17.2.12.11.2.1.4

fsTankVolume OBJECT-TYPE
    SYNTAX DisplayString
    MAX-ACCESS read-write
    STATUS current
    DESCRIPTION
        "How many volume units the tank contains, when full.  This is a
        floating point value."
    ::= { fsTankEntry 5 }
    --1.3.6.1.4.1.3052.17.2.12.11.2.1.5

fsTankVolumeUnit OBJECT-TYPE
    SYNTAX DisplayString
    MAX-ACCESS read-write
    STATUS current
    DESCRIPTION
        "Name of the unit representing fluid volume in the tank. This is only
        used for display purposes; it does not affect the volume calculation."
    ::= { fsTankEntry 6 }
    --1.3.6.1.4.1.3052.17.2.12.11.2.1.6

fsTankShape OBJECT-TYPE
    SYNTAX DisplayString
    MAX-ACCESS read-write
    STATUS current
    DESCRIPTION
        "The shape of the fuel tank.  A value of LINEAR produces a fluid
        volume reading that is directly proportional to fluid height.  The
        HORIZ CYL and HORIZ OVAL settings use a hard-coded formula to
        calculate the volume.  The CUSTOM setting uses a strapping table that
        must be configured as well (see fuelSensorCustomTankTable)."
    ::= { fsTankEntry 7 }
    --1.3.6.1.4.1.3052.17.2.12.11.2.1.7


fuelSensorCustomTankTable OBJECT-TYPE
    SYNTAX SEQUENCE OF FuelSensorConfigCustomTankStrapping
    MAX-ACCESS not-accessible
    STATUS current
    DESCRIPTION
        "This table organizes the custom tank strapping table.  Each fuel
        sensor has a table of height/volume pairs in service only when the tank
        shape (fsTankShape) in CUSTOM.  This allows the unit to calculate
        volumes for nonstandard tank shapes, to the degree that accurate
        height/volume measurements can be configured.  This SNMP table has two
        indexes: the first for which fuel sensor and the second for which
        height/volume pair."
    ::= { fuelSensor 3 }
    --1.3.6.1.4.1.3052.17.2.12.11.3

fsCustomTankEntry OBJECT-TYPE
    SYNTAX FuelSensorConfigCustomTankStrapping
    MAX-ACCESS not-accessible
    STATUS current
    DESCRIPTION
        "Entry for fuel sensor custom tank config table."
    INDEX { fsCustomTankIndexFS, fsCustomTankIndexDatum }
    ::= { fuelSensorCustomTankTable 1 }
    --1.3.6.1.4.1.3052.17.2.12.11.3.1

fsCustomTankIndexFS OBJECT-TYPE
    SYNTAX Integer32 (1..3)
    MAX-ACCESS read-only
    STATUS current
    DESCRIPTION
        "Which fuel sensor in the fuel sensor tank config table.  This is the
        first of two indexes for this SNMP table."
    ::= { fsCustomTankEntry 1 }
    --1.3.6.1.4.1.3052.17.2.12.11.3.1.1

fsCustomTankIndexDatum OBJECT-TYPE
    SYNTAX Integer32 (1..32)
    MAX-ACCESS read-only
    STATUS current
    DESCRIPTION
        "Which hight/volume pair: there are 32 pairs per fuel sensor.  This is
        the second of two indexes for this SNMP table."
    ::= { fsCustomTankEntry 2 }
    --1.3.6.1.4.1.3052.17.2.12.11.3.1.2

fsCustomTankHeight OBJECT-TYPE
    SYNTAX DisplayString
    MAX-ACCESS read-write
    STATUS current
    DESCRIPTION
        "Height of custom tank height/volume pair.  This is a floating point
        value."
    ::= { fsCustomTankEntry 3 }
    --1.3.6.1.4.1.3052.17.2.12.11.3.1.3

fsCustomTankVolume OBJECT-TYPE
    SYNTAX DisplayString
    MAX-ACCESS read-write
    STATUS current
    DESCRIPTION
        "Volume of custom tank height/volume pair.  This is a floating point
        value."
    ::= { fsCustomTankEntry 4 }
    --1.3.6.1.4.1.3052.17.2.12.11.3.1.4


fuelSensorVolumeTable OBJECT-TYPE
    SYNTAX SEQUENCE OF FuelSensorConfigVolume
    MAX-ACCESS not-accessible
    STATUS current
    DESCRIPTION
        "This table organizes volume-event-specific fuel sensor attributes."
    ::= { fuelSensor 4 }
    --1.3.6.1.4.1.3052.17.2.12.11.4

fsVolumeEntry OBJECT-TYPE
    SYNTAX FuelSensorConfigVolume
    MAX-ACCESS not-accessible
    STATUS current
    DESCRIPTION
        "Entry for fuel sensor volume event config table."
    INDEX { fsVolumeIndex }
    ::= { fuelSensorVolumeTable 1 }
    --1.3.6.1.4.1.3052.17.2.12.11.4.1

fsVolumeIndex OBJECT-TYPE
    SYNTAX Integer32 (1..3)
    MAX-ACCESS read-only
    STATUS current
    DESCRIPTION
        "Which fuel sensor in the fuel sensor volume event config table."
    ::= { fsVolumeEntry 1 }
    --1.3.6.1.4.1.3052.17.2.12.11.4.1.1

fsVolumeEnable OBJECT-TYPE
    SYNTAX DisplayString
    MAX-ACCESS read-write
    STATUS current
    DESCRIPTION
        "Enable fuel sensor volume events."
    ::= { fsVolumeEntry 2 }
    --1.3.6.1.4.1.3052.17.2.12.11.4.1.2

fsVolumeDeadband OBJECT-TYPE
    SYNTAX DisplayString
    MAX-ACCESS read-write
    STATUS current
    DESCRIPTION
        "Fuel sensor deadband (hysteresis).  This is a floating point value."
    ::= { fsVolumeEntry 3 }
    --1.3.6.1.4.1.3052.17.2.12.11.4.1.3

fsVolumeVHighValue OBJECT-TYPE
    SYNTAX DisplayString
    MAX-ACCESS read-write
    STATUS current
    DESCRIPTION
        "Fuel sensor volume very high event threshold value.  This is a
        floating point value."
    ::= { fsVolumeEntry 4 }
    --1.3.6.1.4.1.3052.17.2.12.11.4.1.4

fsVolumeVHighActions OBJECT-TYPE
    SYNTAX DisplayString
    MAX-ACCESS read-write
    STATUS current
    DESCRIPTION
        "Fuel sensor volume very high event threshold actions."
    ::= { fsVolumeEntry 5 }
    --1.3.6.1.4.1.3052.17.2.12.11.4.1.5

fsVolumeVHighTrapNum OBJECT-TYPE
    SYNTAX Integer32 (519..1199)
    MAX-ACCESS read-write
    STATUS current
    DESCRIPTION
        "Fuel sensor volume very high event threshold trap number."
    ::= { fsVolumeEntry 6 }
    --1.3.6.1.4.1.3052.17.2.12.11.4.1.6

fsVolumeVHighClass OBJECT-TYPE
    SYNTAX DisplayString
    MAX-ACCESS read-write
    STATUS current
    DESCRIPTION
        "Fuel sensor volume very high event threshold class (severity)."
    ::= { fsVolumeEntry 7 }
    --1.3.6.1.4.1.3052.17.2.12.11.4.1.7

fsVolumeHighValue OBJECT-TYPE
    SYNTAX DisplayString
    MAX-ACCESS read-write
    STATUS current
    DESCRIPTION
        "Fuel sensor volume high event threshold value.  This is a floating
        point value."
    ::= { fsVolumeEntry 8 }
    --1.3.6.1.4.1.3052.17.2.12.11.4.1.8

fsVolumeHighActions OBJECT-TYPE
    SYNTAX DisplayString
    MAX-ACCESS read-write
    STATUS current
    DESCRIPTION
        "Fuel sensor volume high event threshold actions."
    ::= { fsVolumeEntry 9 }
    --1.3.6.1.4.1.3052.17.2.12.11.4.1.9

fsVolumeHighTrapNum OBJECT-TYPE
    SYNTAX Integer32 (519..1199)
    MAX-ACCESS read-write
    STATUS current
    DESCRIPTION
        "Fuel sensor volume high event threshold trap number."
    ::= { fsVolumeEntry 10 }
    --1.3.6.1.4.1.3052.17.2.12.11.4.1.10

fsVolumeHighClass OBJECT-TYPE
    SYNTAX DisplayString
    MAX-ACCESS read-write
    STATUS current
    DESCRIPTION
        "Fuel sensor volume high event threshold class (severity)."
    ::= { fsVolumeEntry 11 }
    --1.3.6.1.4.1.3052.17.2.12.11.4.1.11

fsVolumeNormalActions OBJECT-TYPE
    SYNTAX DisplayString
    MAX-ACCESS read-write
    STATUS current
    DESCRIPTION
        "Fuel sensor volume return to normal actions."
    ::= { fsVolumeEntry 12 }
    --1.3.6.1.4.1.3052.17.2.12.11.4.1.12

fsVolumeNormalTrapNum OBJECT-TYPE
    SYNTAX Integer32 (519..1199)
    MAX-ACCESS read-write
    STATUS current
    DESCRIPTION
        "Fuel sensor volume return to normal trap number."
    ::= { fsVolumeEntry 13 }
    --1.3.6.1.4.1.3052.17.2.12.11.4.1.13

fsVolumeNormalClass OBJECT-TYPE
    SYNTAX DisplayString
    MAX-ACCESS read-write
    STATUS current
    DESCRIPTION
        "Fuel sensor volume return to normal class (severity)."
    ::= { fsVolumeEntry 14 }
    --1.3.6.1.4.1.3052.17.2.12.11.4.1.14

fsVolumeLowValue OBJECT-TYPE
    SYNTAX DisplayString
    MAX-ACCESS read-write
    STATUS current
    DESCRIPTION
        "Fuel sensor volume low event threshold value.  This is a floating
        point value."
    ::= { fsVolumeEntry 15 }
    --1.3.6.1.4.1.3052.17.2.12.11.4.1.15

fsVolumeLowActions OBJECT-TYPE
    SYNTAX DisplayString
    MAX-ACCESS read-write
    STATUS current
    DESCRIPTION
        "Fuel sensor volume low event threshold actions."
    ::= { fsVolumeEntry 16 }
    --1.3.6.1.4.1.3052.17.2.12.11.4.1.16

fsVolumeLowTrapNum OBJECT-TYPE
    SYNTAX Integer32 (519..1199)
    MAX-ACCESS read-write
    STATUS current
    DESCRIPTION
        "Fuel sensor volume low event threshold trap number."
    ::= { fsVolumeEntry 17 }
    --1.3.6.1.4.1.3052.17.2.12.11.4.1.17

fsVolumeLowClass OBJECT-TYPE
    SYNTAX DisplayString
    MAX-ACCESS read-write
    STATUS current
    DESCRIPTION
        "Fuel sensor volume low event threshold class (severity)."
    ::= { fsVolumeEntry 18 }
    --1.3.6.1.4.1.3052.17.2.12.11.4.1.18

fsVolumeVLowValue OBJECT-TYPE
    SYNTAX DisplayString
    MAX-ACCESS read-write
    STATUS current
    DESCRIPTION
        "Fuel sensor volume very low event threshold value.  This is a
        floating point value."
    ::= { fsVolumeEntry 19 }
    --1.3.6.1.4.1.3052.17.2.12.11.4.1.19

fsVolumeVLowActions OBJECT-TYPE
    SYNTAX DisplayString
    MAX-ACCESS read-write
    STATUS current
    DESCRIPTION
        "Fuel sensor volume very low event threshold actions."
    ::= { fsVolumeEntry 20 }
    --1.3.6.1.4.1.3052.17.2.12.11.4.1.20

fsVolumeVLowTrapNum OBJECT-TYPE
    SYNTAX Integer32 (519..1199)
    MAX-ACCESS read-write
    STATUS current
    DESCRIPTION
        "Fuel sensor volume very low event threshold trap number."
    ::= { fsVolumeEntry 21 }
    --1.3.6.1.4.1.3052.17.2.12.11.4.1.21

fsVolumeVLowClass OBJECT-TYPE
    SYNTAX DisplayString
    MAX-ACCESS read-write
    STATUS current
    DESCRIPTION
        "Fuel sensor volume very low event threshold class (severity)."
    ::= { fsVolumeEntry 22 }
    --1.3.6.1.4.1.3052.17.2.12.11.4.1.22



fuelSensorDisconnectTable OBJECT-TYPE
    SYNTAX SEQUENCE OF FuelSensorConfigDisconnect
    MAX-ACCESS not-accessible
    STATUS current
    DESCRIPTION
        "This table organizes disconnect-event-specific fuel sensor attributes."
    ::= { fuelSensor 5 }
    --1.3.6.1.4.1.3052.17.2.12.11.5

fsDiscEntry OBJECT-TYPE
    SYNTAX FuelSensorConfigDisconnect
    MAX-ACCESS not-accessible
    STATUS current
    DESCRIPTION
        "Entry for fuel sensor disconnect event config table."
    INDEX { fsDiscIndex }
    ::= { fuelSensorDisconnectTable 1 }
    --1.3.6.1.4.1.3052.17.2.12.11.5.1

fsDiscIndex OBJECT-TYPE
    SYNTAX Integer32 (1..3)
    MAX-ACCESS read-only
    STATUS current
    DESCRIPTION
        "Which fuel sensor in the fuel sensor disconnect event config table."
    ::= { fsDiscEntry 1 }
    --1.3.6.1.4.1.3052.17.2.12.11.5.1.1

fsDiscEnable OBJECT-TYPE
    SYNTAX DisplayString
    MAX-ACCESS read-write
    STATUS current
    DESCRIPTION
        "Fuel sensor disconnect event enable."
    ::= { fsDiscEntry 2 }
    --1.3.6.1.4.1.3052.17.2.12.11.5.1.2

fsDiscHighValue OBJECT-TYPE
    SYNTAX Integer32
    MAX-ACCESS read-write
    STATUS current
    DESCRIPTION
        "High end of input value range when fuel sensor is disconnected.  This
        is in the units of the analog input value."
    ::= { fsDiscEntry 3 }
    --1.3.6.1.4.1.3052.17.2.12.11.5.1.3

fsDiscLowValue OBJECT-TYPE
    SYNTAX Integer32
    MAX-ACCESS read-write
    STATUS current
    DESCRIPTION
        "Low end of input value range when fuel sensor is disconnected.  This
        is in the units of the analog input value."
    ::= { fsDiscEntry 4 }
    --1.3.6.1.4.1.3052.17.2.12.11.5.1.4

fsDiscActions OBJECT-TYPE
    SYNTAX DisplayString
    MAX-ACCESS read-write
    STATUS current
    DESCRIPTION
        "Fuel sensor disconnect event actions."
    ::= { fsDiscEntry 5 }
    --1.3.6.1.4.1.3052.17.2.12.11.5.1.5

fsDiscTrapNum OBJECT-TYPE
    SYNTAX Integer32 (515..1199)
    MAX-ACCESS read-write
    STATUS current
    DESCRIPTION
        "Fuel sensor disconnect event trap number."
    ::= { fsDiscEntry 6 }
    --1.3.6.1.4.1.3052.17.2.12.11.5.1.6

fsDiscClass OBJECT-TYPE
    SYNTAX DisplayString
    MAX-ACCESS read-write
    STATUS current
    DESCRIPTION
        "Fuel sensor disconnect event class (severity)."
    ::= { fsDiscEntry 7 }
    --1.3.6.1.4.1.3052.17.2.12.11.5.1.7

fsDiscNormalActions OBJECT-TYPE
    SYNTAX DisplayString
    MAX-ACCESS read-write
    STATUS current
    DESCRIPTION
        "Fuel sensor disconnect return to normal actions."
    ::= { fsDiscEntry 8 }
    --1.3.6.1.4.1.3052.17.2.12.11.5.1.8

fsDiscNormalTrapNum OBJECT-TYPE
    SYNTAX Integer32 (515..1199)
    MAX-ACCESS read-write
    STATUS current
    DESCRIPTION
        "Fuel sensor disconnect return to normal trap number."
    ::= { fsDiscEntry 9 }
    --1.3.6.1.4.1.3052.17.2.12.11.5.1.9

fsDiscNormalClass OBJECT-TYPE
    SYNTAX DisplayString
    MAX-ACCESS read-write
    STATUS current
    DESCRIPTION
        "Fuel sensor disconnect return to normal class (severity)."
    ::= { fsDiscEntry 10 }
    --1.3.6.1.4.1.3052.17.2.12.11.5.1.10


fuelSensorSuddenChangeTable OBJECT-TYPE
    SYNTAX SEQUENCE OF FuelSensorConfigSuddenChange
    MAX-ACCESS not-accessible
    STATUS current
    DESCRIPTION
        "This table organizes sudden-change-event-specific fuel sensor
        attributes."
    ::= { fuelSensor 6 }
    --1.3.6.1.4.1.3052.17.2.12.11.6

fsSuddenChangeEntry OBJECT-TYPE
    SYNTAX FuelSensorConfigSuddenChange
    MAX-ACCESS not-accessible
    STATUS current
    DESCRIPTION
        "Entry for fuel sensor sudden change event config table."
    INDEX { fsSuddenChangeIndex }
    ::= { fuelSensorSuddenChangeTable 1 }
    --1.3.6.1.4.1.3052.17.2.12.11.6.1

fsSuddenChangeIndex OBJECT-TYPE
    SYNTAX Integer32 (1..3)
    MAX-ACCESS read-only
    STATUS current
    DESCRIPTION
        "Which fuel sensor in the fuel sensor disconnect event config table."
    ::= { fsSuddenChangeEntry 1 }
    --1.3.6.1.4.1.3052.17.2.12.11.6.1.1

fsSuddenChangeEnable OBJECT-TYPE
    SYNTAX DisplayString
    MAX-ACCESS read-write
    STATUS current
    DESCRIPTION
        "Fuel volume sudden change event enable."
    ::= { fsSuddenChangeEntry 2 }
    --1.3.6.1.4.1.3052.17.2.12.11.6.1.2

fsSuddenChangeTime OBJECT-TYPE
    SYNTAX Integer32 (5..360)
    MAX-ACCESS read-write
    STATUS current
    DESCRIPTION
        "Fuel volume sudden change event time (minutes): what duration defines
        'sudden'."
    ::= { fsSuddenChangeEntry 3 }
    --1.3.6.1.4.1.3052.17.2.12.11.6.1.3

fsSuddenChangeAmplitude OBJECT-TYPE
    SYNTAX DisplayString
    MAX-ACCESS read-write
    STATUS current
    DESCRIPTION
        "Fuel volume sudden change event amplitude: what amount (in fuel
        volume units) over the duration (fsSuddenChangeTime) defines enough
        change."
    ::= { fsSuddenChangeEntry 4 }
    --1.3.6.1.4.1.3052.17.2.12.11.6.1.4

fsSuddenChangeActions OBJECT-TYPE
    SYNTAX DisplayString
    MAX-ACCESS read-write
    STATUS current
    DESCRIPTION
        "Fuel volume sudden change event actions."
    ::= { fsSuddenChangeEntry 5 }
    --1.3.6.1.4.1.3052.17.2.12.11.6.1.5

fsSuddenChangeTrapNum OBJECT-TYPE
    SYNTAX Integer32 (527..1199)
    MAX-ACCESS read-write
    STATUS current
    DESCRIPTION
        "Fuel volume sudden change event trap number."
    ::= { fsSuddenChangeEntry 6 }
    --1.3.6.1.4.1.3052.17.2.12.11.6.1.6

fsSuddenChangeClass OBJECT-TYPE
    SYNTAX DisplayString
    MAX-ACCESS read-write
    STATUS current
    DESCRIPTION
        "Fuel volume sudden change event class (severity)."
    ::= { fsSuddenChangeEntry 7 }
    --1.3.6.1.4.1.3052.17.2.12.11.6.1.7


fuelSensorSlowChangeTable OBJECT-TYPE
    SYNTAX SEQUENCE OF FuelSensorConfigSlowChange
    MAX-ACCESS not-accessible
    STATUS current
    DESCRIPTION
        "This table organizes slow-change-event-specific fuel sensor attributes."
    ::= { fuelSensor 7 }
    --1.3.6.1.4.1.3052.17.2.12.11.7

fsSlowChangeEntry OBJECT-TYPE
    SYNTAX FuelSensorConfigSlowChange
    MAX-ACCESS not-accessible
    STATUS current
    DESCRIPTION
        "Entry for fuel sensor slow change event config table."
    INDEX { fsSlowChangeIndex }
    ::= { fuelSensorSlowChangeTable 1 }
    --1.3.6.1.4.1.3052.17.2.12.11.7.1

fsSlowChangeIndex OBJECT-TYPE
    SYNTAX Integer32 (1..3)
    MAX-ACCESS read-only
    STATUS current
    DESCRIPTION
        "Which fuel sensor in the fuel sensor disconnect event config table."
    ::= { fsSlowChangeEntry 1 }
    --1.3.6.1.4.1.3052.17.2.12.11.7.1.1

fsSlowChangeEnable OBJECT-TYPE
    SYNTAX DisplayString
    MAX-ACCESS read-write
    STATUS current
    DESCRIPTION
        "Fuel volume slow change event enable."
    ::= { fsSlowChangeEntry 2 }
    --1.3.6.1.4.1.3052.17.2.12.11.7.1.2

fsSlowChangeTime OBJECT-TYPE
    SYNTAX Integer32 (1..168)
    MAX-ACCESS read-write
    STATUS current
    DESCRIPTION
        "Fuel volume slow change event time (minutes): what duration defines
        'slow'."
    ::= { fsSlowChangeEntry 3 }
    --1.3.6.1.4.1.3052.17.2.12.11.7.1.3

fsSlowChangeAmplitude OBJECT-TYPE
    SYNTAX DisplayString
    MAX-ACCESS read-write
    STATUS current
    DESCRIPTION
        "Fuel volume slow change event amplitude: what amount (in fuel volume
        units) over the duration (fsSlowChangeTime) defines enough change."
    ::= { fsSlowChangeEntry 4 }
    --1.3.6.1.4.1.3052.17.2.12.11.7.1.4

fsSlowChangeActions OBJECT-TYPE
    SYNTAX DisplayString
    MAX-ACCESS read-write
    STATUS current
    DESCRIPTION
        "Fuel volume slow change event actions."
    ::= { fsSlowChangeEntry 5 }
    --1.3.6.1.4.1.3052.17.2.12.11.7.1.5

fsSlowChangeTrapNum OBJECT-TYPE
    SYNTAX Integer32 (528..1199)
    MAX-ACCESS read-write
    STATUS current
    DESCRIPTION
        "Fuel volume slow change event trap number."
    ::= { fsSlowChangeEntry 6 }
    --1.3.6.1.4.1.3052.17.2.12.11.7.1.6

fsSlowChangeClass OBJECT-TYPE
    SYNTAX DisplayString
    MAX-ACCESS read-write
    STATUS current
    DESCRIPTION
        "Fuel volume slow change event class (severity)."
    ::= { fsSlowChangeEntry 7 }
    --1.3.6.1.4.1.3052.17.2.12.11.7.1.7


--***************************************************************************************
--AC Power Monitor Config Section       2.12.12
--***************************************************************************************

acpmGeneralTable OBJECT-TYPE
    SYNTAX SEQUENCE OF ACPMConfigGeneral
    MAX-ACCESS not-accessible
    STATUS current
    DESCRIPTION
        "This table organizes general AC power monitor attributes."
    ::= { acPowerMonitor 1 }
    --1.3.6.1.4.1.3052.17.2.12.12.1

acpmGenEntry OBJECT-TYPE
    SYNTAX ACPMConfigGeneral
    MAX-ACCESS not-accessible
    STATUS current
    DESCRIPTION
        "Entry for AC power monitor general config table."
    INDEX { acpmGenIndex }
    ::= { acpmGeneralTable 1 }
    --1.3.6.1.4.1.3052.17.2.12.12.1.1

acpmGenIndex OBJECT-TYPE
    SYNTAX Integer32 (1..6)
    MAX-ACCESS read-only
    STATUS current
    DESCRIPTION
        "Which AC power monitor in the AC power monitor general config table."
    ::= { acpmGenEntry 1 }
    --1.3.6.1.4.1.3052.17.2.12.12.1.1.1

acpmGenDevice OBJECT-TYPE
    SYNTAX DisplayString
    MAX-ACCESS read-write
    STATUS current
    DESCRIPTION
        "Model of the AC power monitor device. The unit needs this setting to
        know which registers to poll for the various data items, among other
        things."
    ::= { acpmGenEntry 2 }
    --1.3.6.1.4.1.3052.17.2.12.12.1.1.2

acpmGenName OBJECT-TYPE
    SYNTAX DisplayString
    MAX-ACCESS read-write
    STATUS current
    DESCRIPTION
        "Name for the AC power monitor device."
    ::= { acpmGenEntry 3 }
    --1.3.6.1.4.1.3052.17.2.12.12.1.1.3

acpmGenAddress OBJECT-TYPE
    SYNTAX Integer32 (1..247)
    MAX-ACCESS read-write
    STATUS current
    DESCRIPTION
        "Modbus address of the AC power monitor device."
    ::= { acpmGenEntry 4 }
    --1.3.6.1.4.1.3052.17.2.12.12.1.1.4

acpmGenPtRatio OBJECT-TYPE
    SYNTAX Integer32 (1..10000)
    MAX-ACCESS read-write
    STATUS current
    DESCRIPTION
        "Ratio of secondary turns to primary turns on potential transformers
        (PT)."
    ::= { acpmGenEntry 5 }
    --1.3.6.1.4.1.3052.17.2.12.12.1.1.5

acpmGenCtRatio OBJECT-TYPE
    SYNTAX Integer32 (1..10000)
    MAX-ACCESS read-write
    STATUS current
    DESCRIPTION
        "Ratio of secondary turns to primary turns on current transformers
        (CT)."
    ::= { acpmGenEntry 6 }
    --1.3.6.1.4.1.3052.17.2.12.12.1.1.6

acpmGenPowerType OBJECT-TYPE
    SYNTAX DisplayString
    MAX-ACCESS read-write
    STATUS current
    DESCRIPTION
        "Type of power being monitored."
    ::= { acpmGenEntry 7 }
    --1.3.6.1.4.1.3052.17.2.12.12.1.1.7

acpmGenSysrepPackage OBJECT-TYPE
    SYNTAX Integer32 (0..10)
    MAX-ACCESS read-write
    STATUS current
    DESCRIPTION
        "System reporting package number."
    ::= { acpmGenEntry 8 }
    --1.3.6.1.4.1.3052.17.2.12.12.1.1.8

acpmGenSysrepType OBJECT-TYPE
    SYNTAX DisplayString
    MAX-ACCESS read-write
    STATUS current
    DESCRIPTION
        "ASM profile type."
    ::= { acpmGenEntry 9 }
    --1.3.6.1.4.1.3052.17.2.12.12.1.1.9


acpmAvgVoltageTable OBJECT-TYPE
    SYNTAX SEQUENCE OF ACPMConfigAvgVoltage
    MAX-ACCESS not-accessible
    STATUS current
    DESCRIPTION
        "This table organizes AC power monitor average voltage attributes."
    ::= { acPowerMonitor 2 }
    --1.3.6.1.4.1.3052.17.2.12.12.2

acpmAvgVoltageEntry OBJECT-TYPE
    SYNTAX ACPMConfigAvgVoltage
    MAX-ACCESS not-accessible
    STATUS current
    DESCRIPTION
        "Entry for AC power monitor average voltage config table."
    INDEX { acpmAvgVoltageIndex }
    ::= { acpmAvgVoltageTable 1 }
    --1.3.6.1.4.1.3052.17.2.12.12.2.1

acpmAvgVoltageIndex OBJECT-TYPE
    SYNTAX Integer32 (1..6)
    MAX-ACCESS read-only
    STATUS current
    DESCRIPTION
        "Which AC power monitor in the AC power monitor average voltage config
        table."
    ::= { acpmAvgVoltageEntry 1 }
    --1.3.6.1.4.1.3052.17.2.12.12.2.1.1

acpmAvgVoltageEnable OBJECT-TYPE
    SYNTAX DisplayString
    MAX-ACCESS read-write
    STATUS current
    DESCRIPTION
        "Enable AC power monitor average voltage events."
    ::= { acpmAvgVoltageEntry 2 }
    --1.3.6.1.4.1.3052.17.2.12.12.2.1.2

acpmAvgVoltageDeadband OBJECT-TYPE
    SYNTAX DisplayString
    MAX-ACCESS read-write
    STATUS current
    DESCRIPTION
        "Deadband (hysteresis) for average voltage event.  This is a floating
        point value."
    ::= { acpmAvgVoltageEntry 3 }
    --1.3.6.1.4.1.3052.17.2.12.12.2.1.3

acpmAvgVoltageVHighValue OBJECT-TYPE
    SYNTAX DisplayString
    MAX-ACCESS read-write
    STATUS current
    DESCRIPTION
        "Very high event threshold.  This is a floating point value."
    ::= { acpmAvgVoltageEntry 4 }
    --1.3.6.1.4.1.3052.17.2.12.12.2.1.4

acpmAvgVoltageVHighActions OBJECT-TYPE
    SYNTAX DisplayString
    MAX-ACCESS read-write
    STATUS current
    DESCRIPTION
        "Very high event actions."
    ::= { acpmAvgVoltageEntry 5 }
    --1.3.6.1.4.1.3052.17.2.12.12.2.1.5

acpmAvgVoltageVHighTrapNum OBJECT-TYPE
    SYNTAX Integer32 (520..1199)
    MAX-ACCESS read-write
    STATUS current
    DESCRIPTION
        "Very high event trap number."
    ::= { acpmAvgVoltageEntry 6 }
    --1.3.6.1.4.1.3052.17.2.12.12.2.1.6

acpmAvgVoltageVHighClass OBJECT-TYPE
    SYNTAX DisplayString
    MAX-ACCESS read-write
    STATUS current
    DESCRIPTION
        "Very high event class."
    ::= { acpmAvgVoltageEntry 7 }
    --1.3.6.1.4.1.3052.17.2.12.12.2.1.7

acpmAvgVoltageHighValue OBJECT-TYPE
    SYNTAX DisplayString
    MAX-ACCESS read-write
    STATUS current
    DESCRIPTION
        "High event threshold.  This is a floating point value."
    ::= { acpmAvgVoltageEntry 8 }
    --1.3.6.1.4.1.3052.17.2.12.12.2.1.8

acpmAvgVoltageHighActions OBJECT-TYPE
    SYNTAX DisplayString
    MAX-ACCESS read-write
    STATUS current
    DESCRIPTION
        "High event actions."
    ::= { acpmAvgVoltageEntry 9 }
    --1.3.6.1.4.1.3052.17.2.12.12.2.1.9

acpmAvgVoltageHighTrapNum OBJECT-TYPE
    SYNTAX Integer32 (520..1199)
    MAX-ACCESS read-write
    STATUS current
    DESCRIPTION
        "High event trap number."
    ::= { acpmAvgVoltageEntry 10 }
    --1.3.6.1.4.1.3052.17.2.12.12.2.1.10

acpmAvgVoltageHighClass OBJECT-TYPE
    SYNTAX DisplayString
    MAX-ACCESS read-write
    STATUS current
    DESCRIPTION
        "High event class."
    ::= { acpmAvgVoltageEntry 11 }
    --1.3.6.1.4.1.3052.17.2.12.12.2.1.11

acpmAvgVoltageNormalActions OBJECT-TYPE
    SYNTAX DisplayString
    MAX-ACCESS read-write
    STATUS current
    DESCRIPTION
        "Return to normal actions."
    ::= { acpmAvgVoltageEntry 12 }
    --1.3.6.1.4.1.3052.17.2.12.12.2.1.12

acpmAvgVoltageNormalTrapNum OBJECT-TYPE
    SYNTAX Integer32 (520..1199)
    MAX-ACCESS read-write
    STATUS current
    DESCRIPTION
        "Return to normal trap number."
    ::= { acpmAvgVoltageEntry 13 }
    --1.3.6.1.4.1.3052.17.2.12.12.2.1.13

acpmAvgVoltageNormalClass OBJECT-TYPE
    SYNTAX DisplayString
    MAX-ACCESS read-write
    STATUS current
    DESCRIPTION
        "Return to normal class."
    ::= { acpmAvgVoltageEntry 14 }
    --1.3.6.1.4.1.3052.17.2.12.12.2.1.14

acpmAvgVoltageLowValue OBJECT-TYPE
    SYNTAX DisplayString
    MAX-ACCESS read-write
    STATUS current
    DESCRIPTION
        "Low event threshold.  This is a floating point value."
    ::= { acpmAvgVoltageEntry 15 }
    --1.3.6.1.4.1.3052.17.2.12.12.2.1.15

acpmAvgVoltageLowActions OBJECT-TYPE
    SYNTAX DisplayString
    MAX-ACCESS read-write
    STATUS current
    DESCRIPTION
        "Low event actions."
    ::= { acpmAvgVoltageEntry 16 }
    --1.3.6.1.4.1.3052.17.2.12.12.2.1.16

acpmAvgVoltageLowTrapNum OBJECT-TYPE
    SYNTAX Integer32 (520..1199)
    MAX-ACCESS read-write
    STATUS current
    DESCRIPTION
        "Low event trap number."
    ::= { acpmAvgVoltageEntry 17 }
    --1.3.6.1.4.1.3052.17.2.12.12.2.1.17

acpmAvgVoltageLowClass OBJECT-TYPE
    SYNTAX DisplayString
    MAX-ACCESS read-write
    STATUS current
    DESCRIPTION
        "Low event class."
    ::= { acpmAvgVoltageEntry 18 }
    --1.3.6.1.4.1.3052.17.2.12.12.2.1.18

acpmAvgVoltageVLowValue OBJECT-TYPE
    SYNTAX DisplayString
    MAX-ACCESS read-write
    STATUS current
    DESCRIPTION
        "Very low event threshold.  This is a floating point value."
    ::= { acpmAvgVoltageEntry 19 }
    --1.3.6.1.4.1.3052.17.2.12.12.2.1.19

acpmAvgVoltageVLowActions OBJECT-TYPE
    SYNTAX DisplayString
    MAX-ACCESS read-write
    STATUS current
    DESCRIPTION
        "Very low event actions."
    ::= { acpmAvgVoltageEntry 20 }
    --1.3.6.1.4.1.3052.17.2.12.12.2.1.20

acpmAvgVoltageVLowTrapNum OBJECT-TYPE
    SYNTAX Integer32 (520..1199)
    MAX-ACCESS read-write
    STATUS current
    DESCRIPTION
        "Very low event trap number."
    ::= { acpmAvgVoltageEntry 21 }
    --1.3.6.1.4.1.3052.17.2.12.12.2.1.21

acpmAvgVoltageVLowClass OBJECT-TYPE
    SYNTAX DisplayString
    MAX-ACCESS read-write
    STATUS current
    DESCRIPTION
        "Very low event class."
    ::= { acpmAvgVoltageEntry 22 }
    --1.3.6.1.4.1.3052.17.2.12.12.2.1.22

acpmAvgVoltageSysrepEnable OBJECT-TYPE
    SYNTAX DisplayString
    MAX-ACCESS read-write
    STATUS current
    DESCRIPTION
        "System reporting enable for average voltage telemetry."
    ::= { acpmAvgVoltageEntry 23 }
    --1.3.6.1.4.1.3052.17.2.12.12.2.1.23

acpmAvgVoltageSysrepThreshold OBJECT-TYPE
    SYNTAX DisplayString
    MAX-ACCESS read-write
    STATUS current
    DESCRIPTION
        "System reporting threshold for average voltage telemetry.  This is a
        floating point value."
    ::= { acpmAvgVoltageEntry 24 }
    --1.3.6.1.4.1.3052.17.2.12.12.2.1.24

acpmAvgVoltageSysrepLimit OBJECT-TYPE
    SYNTAX Integer32
    MAX-ACCESS read-write
    STATUS current
    DESCRIPTION
        "System reporting limit for average voltage telemetry."
    ::= { acpmAvgVoltageEntry 25 }
    --1.3.6.1.4.1.3052.17.2.12.12.2.1.25


acpmAvgCurrentTable OBJECT-TYPE
    SYNTAX SEQUENCE OF ACPMConfigAvgCurrent
    MAX-ACCESS not-accessible
    STATUS current
    DESCRIPTION
        "This table organizes AC power monitor average current attributes."
    ::= { acPowerMonitor 3 }
    --1.3.6.1.4.1.3052.17.2.12.12.3

acpmAvgCurrentEntry OBJECT-TYPE
    SYNTAX ACPMConfigAvgCurrent
    MAX-ACCESS not-accessible
    STATUS current
    DESCRIPTION
        "Entry for AC power monitor average current config table."
    INDEX { acpmAvgCurrentIndex }
    ::= { acpmAvgCurrentTable 1 }
    --1.3.6.1.4.1.3052.17.2.12.12.3.1

acpmAvgCurrentIndex OBJECT-TYPE
    SYNTAX Integer32 (1..6)
    MAX-ACCESS read-only
    STATUS current
    DESCRIPTION
        "Which AC power monitor in the AC power monitor average current config
        table."
    ::= { acpmAvgCurrentEntry 1 }
    --1.3.6.1.4.1.3052.17.2.12.12.3.1.1

acpmAvgCurrentEnable OBJECT-TYPE
    SYNTAX DisplayString
    MAX-ACCESS read-write
    STATUS current
    DESCRIPTION
        "Enable AC power monitor average current events."
    ::= { acpmAvgCurrentEntry 2 }
    --1.3.6.1.4.1.3052.17.2.12.12.3.1.2

acpmAvgCurrentDeadband OBJECT-TYPE
    SYNTAX DisplayString
    MAX-ACCESS read-write
    STATUS current
    DESCRIPTION
        "Deadband (hysteresis) for average current event.  This is a floating
        point value."
    ::= { acpmAvgCurrentEntry 3 }
    --1.3.6.1.4.1.3052.17.2.12.12.3.1.3

acpmAvgCurrentVHighValue OBJECT-TYPE
    SYNTAX DisplayString
    MAX-ACCESS read-write
    STATUS current
    DESCRIPTION
        "Very high event threshold.  This is a floating point value."
    ::= { acpmAvgCurrentEntry 4 }
    --1.3.6.1.4.1.3052.17.2.12.12.3.1.4

acpmAvgCurrentVHighActions OBJECT-TYPE
    SYNTAX DisplayString
    MAX-ACCESS read-write
    STATUS current
    DESCRIPTION
        "Very high event actions."
    ::= { acpmAvgCurrentEntry 5 }
    --1.3.6.1.4.1.3052.17.2.12.12.3.1.5

acpmAvgCurrentVHighTrapNum OBJECT-TYPE
    SYNTAX Integer32 (521..1199)
    MAX-ACCESS read-write
    STATUS current
    DESCRIPTION
        "Very high event trap number."
    ::= { acpmAvgCurrentEntry 6 }
    --1.3.6.1.4.1.3052.17.2.12.12.3.1.6

acpmAvgCurrentVHighClass OBJECT-TYPE
    SYNTAX DisplayString
    MAX-ACCESS read-write
    STATUS current
    DESCRIPTION
        "Very high event class."
    ::= { acpmAvgCurrentEntry 7 }
    --1.3.6.1.4.1.3052.17.2.12.12.3.1.7

acpmAvgCurrentHighValue OBJECT-TYPE
    SYNTAX DisplayString
    MAX-ACCESS read-write
    STATUS current
    DESCRIPTION
        "High event threshold.  This is a floating point value."
    ::= { acpmAvgCurrentEntry 8 }
    --1.3.6.1.4.1.3052.17.2.12.12.3.1.8

acpmAvgCurrentHighActions OBJECT-TYPE
    SYNTAX DisplayString
    MAX-ACCESS read-write
    STATUS current
    DESCRIPTION
        "High event actions."
    ::= { acpmAvgCurrentEntry 9 }
    --1.3.6.1.4.1.3052.17.2.12.12.3.1.9

acpmAvgCurrentHighTrapNum OBJECT-TYPE
    SYNTAX Integer32 (521..1199)
    MAX-ACCESS read-write
    STATUS current
    DESCRIPTION
        "High event trap number."
    ::= { acpmAvgCurrentEntry 10 }
    --1.3.6.1.4.1.3052.17.2.12.12.3.1.10

acpmAvgCurrentHighClass OBJECT-TYPE
    SYNTAX DisplayString
    MAX-ACCESS read-write
    STATUS current
    DESCRIPTION
        "High event class."
    ::= { acpmAvgCurrentEntry 11 }
    --1.3.6.1.4.1.3052.17.2.12.12.3.1.11

acpmAvgCurrentNormalActions OBJECT-TYPE
    SYNTAX DisplayString
    MAX-ACCESS read-write
    STATUS current
    DESCRIPTION
        "Return to normal actions."
    ::= { acpmAvgCurrentEntry 12 }
    --1.3.6.1.4.1.3052.17.2.12.12.3.1.12

acpmAvgCurrentNormalTrapNum OBJECT-TYPE
    SYNTAX Integer32 (521..1199)
    MAX-ACCESS read-write
    STATUS current
    DESCRIPTION
        "Return to normal trap number."
    ::= { acpmAvgCurrentEntry 13 }
    --1.3.6.1.4.1.3052.17.2.12.12.3.1.13

acpmAvgCurrentNormalClass OBJECT-TYPE
    SYNTAX DisplayString
    MAX-ACCESS read-write
    STATUS current
    DESCRIPTION
        "Return to normal class."
    ::= { acpmAvgCurrentEntry 14 }
    --1.3.6.1.4.1.3052.17.2.12.12.3.1.14

acpmAvgCurrentLowValue OBJECT-TYPE
    SYNTAX DisplayString
    MAX-ACCESS read-write
    STATUS current
    DESCRIPTION
        "Low event threshold.  This is a floating point value."
    ::= { acpmAvgCurrentEntry 15 }
    --1.3.6.1.4.1.3052.17.2.12.12.3.1.15

acpmAvgCurrentLowActions OBJECT-TYPE
    SYNTAX DisplayString
    MAX-ACCESS read-write
    STATUS current
    DESCRIPTION
        "Low event actions."
    ::= { acpmAvgCurrentEntry 16 }
    --1.3.6.1.4.1.3052.17.2.12.12.3.1.16

acpmAvgCurrentLowTrapNum OBJECT-TYPE
    SYNTAX Integer32 (521..1199)
    MAX-ACCESS read-write
    STATUS current
    DESCRIPTION
        "Low event trap number."
    ::= { acpmAvgCurrentEntry 17 }
    --1.3.6.1.4.1.3052.17.2.12.12.3.1.17

acpmAvgCurrentLowClass OBJECT-TYPE
    SYNTAX DisplayString
    MAX-ACCESS read-write
    STATUS current
    DESCRIPTION
        "Low event class."
    ::= { acpmAvgCurrentEntry 18 }
    --1.3.6.1.4.1.3052.17.2.12.12.3.1.18

acpmAvgCurrentVLowValue OBJECT-TYPE
    SYNTAX DisplayString
    MAX-ACCESS read-write
    STATUS current
    DESCRIPTION
        "Very low event threshold.  This is a floating point value."
    ::= { acpmAvgCurrentEntry 19 }
    --1.3.6.1.4.1.3052.17.2.12.12.3.1.19

acpmAvgCurrentVLowActions OBJECT-TYPE
    SYNTAX DisplayString
    MAX-ACCESS read-write
    STATUS current
    DESCRIPTION
        "Very low event actions."
    ::= { acpmAvgCurrentEntry 20 }
    --1.3.6.1.4.1.3052.17.2.12.12.3.1.20

acpmAvgCurrentVLowTrapNum OBJECT-TYPE
    SYNTAX Integer32 (521..1199)
    MAX-ACCESS read-write
    STATUS current
    DESCRIPTION
        "Very low event trap number."
    ::= { acpmAvgCurrentEntry 21 }
    --1.3.6.1.4.1.3052.17.2.12.12.3.1.21

acpmAvgCurrentVLowClass OBJECT-TYPE
    SYNTAX DisplayString
    MAX-ACCESS read-write
    STATUS current
    DESCRIPTION
        "Very low event class."
    ::= { acpmAvgCurrentEntry 22 }
    --1.3.6.1.4.1.3052.17.2.12.12.3.1.22

acpmAvgCurrentSysrepEnable OBJECT-TYPE
    SYNTAX DisplayString
    MAX-ACCESS read-write
    STATUS current
    DESCRIPTION
        "System reporting enable for average current telemetry."
    ::= { acpmAvgCurrentEntry 23 }
    --1.3.6.1.4.1.3052.17.2.12.12.3.1.23

acpmAvgCurrentSysrepThreshold OBJECT-TYPE
    SYNTAX DisplayString
    MAX-ACCESS read-write
    STATUS current
    DESCRIPTION
        "System reporting threshold for average current telemetry.  This is
        a floating point value."
    ::= { acpmAvgCurrentEntry 24 }
    --1.3.6.1.4.1.3052.17.2.12.12.3.1.24

acpmAvgCurrentSysrepLimit OBJECT-TYPE
    SYNTAX Integer32
    MAX-ACCESS read-write
    STATUS current
    DESCRIPTION
        "System reporting limit for average current telemetry."
    ::= { acpmAvgCurrentEntry 25 }
    --1.3.6.1.4.1.3052.17.2.12.12.3.1.25


acpmFreqTable OBJECT-TYPE
    SYNTAX SEQUENCE OF ACPMConfigFreq
    MAX-ACCESS not-accessible
    STATUS current
    DESCRIPTION
        "This table organizes AC power monitor frequency attributes."
    ::= { acPowerMonitor 4 }
    --1.3.6.1.4.1.3052.17.2.12.12.4

acpmFreqEntry OBJECT-TYPE
    SYNTAX ACPMConfigFreq
    MAX-ACCESS not-accessible
    STATUS current
    DESCRIPTION
        "Entry for AC power monitor frequency config table."
    INDEX { acpmFreqIndex }
    ::= { acpmFreqTable 1 }
    --1.3.6.1.4.1.3052.17.2.12.12.4.1

acpmFreqIndex OBJECT-TYPE
    SYNTAX Integer32 (1..6)
    MAX-ACCESS read-only
    STATUS current
    DESCRIPTION
        "Which AC power monitor in the AC power monitor frequency config table."
    ::= { acpmFreqEntry 1 }
    --1.3.6.1.4.1.3052.17.2.12.12.4.1.1

acpmFreqEnable OBJECT-TYPE
    SYNTAX DisplayString
    MAX-ACCESS read-write
    STATUS current
    DESCRIPTION
        "Enable AC power monitor frequency events."
    ::= { acpmFreqEntry 2 }
    --1.3.6.1.4.1.3052.17.2.12.12.4.1.2

acpmFreqDeadband OBJECT-TYPE
    SYNTAX DisplayString
    MAX-ACCESS read-write
    STATUS current
    DESCRIPTION
        "Deadband (hysteresis) for frequency event.  This is a floating point
        value."
    ::= { acpmFreqEntry 3 }
    --1.3.6.1.4.1.3052.17.2.12.12.4.1.3

acpmFreqVHighValue OBJECT-TYPE
    SYNTAX DisplayString
    MAX-ACCESS read-write
    STATUS current
    DESCRIPTION
        "Very high event threshold.  This is a floating point value."
    ::= { acpmFreqEntry 4 }
    --1.3.6.1.4.1.3052.17.2.12.12.4.1.4

acpmFreqVHighActions OBJECT-TYPE
    SYNTAX DisplayString
    MAX-ACCESS read-write
    STATUS current
    DESCRIPTION
        "Very high event actions."
    ::= { acpmFreqEntry 5 }
    --1.3.6.1.4.1.3052.17.2.12.12.4.1.5

acpmFreqVHighTrapNum OBJECT-TYPE
    SYNTAX Integer32 (522..1199)
    MAX-ACCESS read-write
    STATUS current
    DESCRIPTION
        "Very high event trap number."
    ::= { acpmFreqEntry 6 }
    --1.3.6.1.4.1.3052.17.2.12.12.4.1.6

acpmFreqVHighClass OBJECT-TYPE
    SYNTAX DisplayString
    MAX-ACCESS read-write
    STATUS current
    DESCRIPTION
        "Very high event class."
    ::= { acpmFreqEntry 7 }
    --1.3.6.1.4.1.3052.17.2.12.12.4.1.7

acpmFreqHighValue OBJECT-TYPE
    SYNTAX DisplayString
    MAX-ACCESS read-write
    STATUS current
    DESCRIPTION
        "High event threshold.  This is a floating point value."
    ::= { acpmFreqEntry 8 }
    --1.3.6.1.4.1.3052.17.2.12.12.4.1.8

acpmFreqHighActions OBJECT-TYPE
    SYNTAX DisplayString
    MAX-ACCESS read-write
    STATUS current
    DESCRIPTION
        "High event actions."
    ::= { acpmFreqEntry 9 }
    --1.3.6.1.4.1.3052.17.2.12.12.4.1.9

acpmFreqHighTrapNum OBJECT-TYPE
    SYNTAX Integer32 (522..1199)
    MAX-ACCESS read-write
    STATUS current
    DESCRIPTION
        "High event trap number."
    ::= { acpmFreqEntry 10 }
    --1.3.6.1.4.1.3052.17.2.12.12.4.1.10

acpmFreqHighClass OBJECT-TYPE
    SYNTAX DisplayString
    MAX-ACCESS read-write
    STATUS current
    DESCRIPTION
        "High event class."
    ::= { acpmFreqEntry 11 }
    --1.3.6.1.4.1.3052.17.2.12.12.4.1.11

acpmFreqNormalActions OBJECT-TYPE
    SYNTAX DisplayString
    MAX-ACCESS read-write
    STATUS current
    DESCRIPTION
        "Return to normal actions."
    ::= { acpmFreqEntry 12 }
    --1.3.6.1.4.1.3052.17.2.12.12.4.1.12

acpmFreqNormalTrapNum OBJECT-TYPE
    SYNTAX Integer32 (522..1199)
    MAX-ACCESS read-write
    STATUS current
    DESCRIPTION
        "Return to normal trap number."
    ::= { acpmFreqEntry 13 }
    --1.3.6.1.4.1.3052.17.2.12.12.4.1.13

acpmFreqNormalClass OBJECT-TYPE
    SYNTAX DisplayString
    MAX-ACCESS read-write
    STATUS current
    DESCRIPTION
        "Return to normal class."
    ::= { acpmFreqEntry 14 }
    --1.3.6.1.4.1.3052.17.2.12.12.4.1.14

acpmFreqLowValue OBJECT-TYPE
    SYNTAX DisplayString
    MAX-ACCESS read-write
    STATUS current
    DESCRIPTION
        "Low event threshold.  This is a floating point value."
    ::= { acpmFreqEntry 15 }
    --1.3.6.1.4.1.3052.17.2.12.12.4.1.15

acpmFreqLowActions OBJECT-TYPE
    SYNTAX DisplayString
    MAX-ACCESS read-write
    STATUS current
    DESCRIPTION
        "Low event actions."
    ::= { acpmFreqEntry 16 }
    --1.3.6.1.4.1.3052.17.2.12.12.4.1.16

acpmFreqLowTrapNum OBJECT-TYPE
    SYNTAX Integer32 (522..1199)
    MAX-ACCESS read-write
    STATUS current
    DESCRIPTION
        "Low event trap number."
    ::= { acpmFreqEntry 17 }
    --1.3.6.1.4.1.3052.17.2.12.12.4.1.17

acpmFreqLowClass OBJECT-TYPE
    SYNTAX DisplayString
    MAX-ACCESS read-write
    STATUS current
    DESCRIPTION
        "Low event class."
    ::= { acpmFreqEntry 18 }
    --1.3.6.1.4.1.3052.17.2.12.12.4.1.18

acpmFreqVLowValue OBJECT-TYPE
    SYNTAX DisplayString
    MAX-ACCESS read-write
    STATUS current
    DESCRIPTION
        "Very low event threshold.  This is a floating point value."
    ::= { acpmFreqEntry 19 }
    --1.3.6.1.4.1.3052.17.2.12.12.4.1.19

acpmFreqVLowActions OBJECT-TYPE
    SYNTAX DisplayString
    MAX-ACCESS read-write
    STATUS current
    DESCRIPTION
        "Very low event actions."
    ::= { acpmFreqEntry 20 }
    --1.3.6.1.4.1.3052.17.2.12.12.4.1.20

acpmFreqVLowTrapNum OBJECT-TYPE
    SYNTAX Integer32 (522..1199)
    MAX-ACCESS read-write
    STATUS current
    DESCRIPTION
        "Very low event trap number."
    ::= { acpmFreqEntry 21 }
    --1.3.6.1.4.1.3052.17.2.12.12.4.1.21

acpmFreqVLowClass OBJECT-TYPE
    SYNTAX DisplayString
    MAX-ACCESS read-write
    STATUS current
    DESCRIPTION
        "Very low event class."
    ::= { acpmFreqEntry 22 }
    --1.3.6.1.4.1.3052.17.2.12.12.4.1.22

acpmFreqSysrepEnable OBJECT-TYPE
    SYNTAX DisplayString
    MAX-ACCESS read-write
    STATUS current
    DESCRIPTION
        "System reporting enable for frequency telemetry."
    ::= { acpmFreqEntry 23 }
    --1.3.6.1.4.1.3052.17.2.12.12.4.1.23

acpmFreqSysrepThreshold OBJECT-TYPE
    SYNTAX DisplayString
    MAX-ACCESS read-write
    STATUS current
    DESCRIPTION
        "System reporting threshold for frequency telemetry.  This is a
        floating point value."
    ::= { acpmFreqEntry 24 }
    --1.3.6.1.4.1.3052.17.2.12.12.4.1.24

acpmFreqSysrepLimit OBJECT-TYPE
    SYNTAX Integer32
    MAX-ACCESS read-write
    STATUS current
    DESCRIPTION
        "System reporting limit for frequency telemetry."
    ::= { acpmFreqEntry 25 }
    --1.3.6.1.4.1.3052.17.2.12.12.4.1.25


acpmTotalRealPowerTable OBJECT-TYPE
    SYNTAX SEQUENCE OF ACPMConfigTRP
    MAX-ACCESS not-accessible
    STATUS current
    DESCRIPTION
        "This table organizes AC power monitor total real power attributes."
    ::= { acPowerMonitor 5 }
    --1.3.6.1.4.1.3052.17.2.12.12.5

acpmTRPEntry OBJECT-TYPE
    SYNTAX ACPMConfigTRP
    MAX-ACCESS not-accessible
    STATUS current
    DESCRIPTION
        "Entry for AC power monitor total real power config table."
    INDEX { acpmTRPIndex }
    ::= { acpmTotalRealPowerTable 1 }
    --1.3.6.1.4.1.3052.17.2.12.12.5.1

acpmTRPIndex OBJECT-TYPE
    SYNTAX Integer32 (1..6)
    MAX-ACCESS read-only
    STATUS current
    DESCRIPTION
        "Which AC power monitor in the AC power monitor total real power
        config table."
    ::= { acpmTRPEntry 1 }
    --1.3.6.1.4.1.3052.17.2.12.12.5.1.1

acpmTRPEnable OBJECT-TYPE
    SYNTAX DisplayString
    MAX-ACCESS read-write
    STATUS current
    DESCRIPTION
        "Enable AC power monitor total real power events."
    ::= { acpmTRPEntry 2 }
    --1.3.6.1.4.1.3052.17.2.12.12.5.1.2

acpmTRPDeadband OBJECT-TYPE
    SYNTAX DisplayString
    MAX-ACCESS read-write
    STATUS current
    DESCRIPTION
        "Deadband (hysteresis) for total real power event.  This is a
        floating point value."
    ::= { acpmTRPEntry 3 }
    --1.3.6.1.4.1.3052.17.2.12.12.5.1.3

acpmTRPVHighValue OBJECT-TYPE
    SYNTAX DisplayString
    MAX-ACCESS read-write
    STATUS current
    DESCRIPTION
        "Very high event threshold.  This is a floating point value."
    ::= { acpmTRPEntry 4 }
    --1.3.6.1.4.1.3052.17.2.12.12.5.1.4

acpmTRPVHighActions OBJECT-TYPE
    SYNTAX DisplayString
    MAX-ACCESS read-write
    STATUS current
    DESCRIPTION
        "Very high event actions."
    ::= { acpmTRPEntry 5 }
    --1.3.6.1.4.1.3052.17.2.12.12.5.1.5

acpmTRPVHighTrapNum OBJECT-TYPE
    SYNTAX Integer32 (523..1199)
    MAX-ACCESS read-write
    STATUS current
    DESCRIPTION
        "Very high event trap number."
    ::= { acpmTRPEntry 6 }
    --1.3.6.1.4.1.3052.17.2.12.12.5.1.6

acpmTRPVHighClass OBJECT-TYPE
    SYNTAX DisplayString
    MAX-ACCESS read-write
    STATUS current
    DESCRIPTION
        "Very high event class."
    ::= { acpmTRPEntry 7 }
    --1.3.6.1.4.1.3052.17.2.12.12.5.1.7

acpmTRPHighValue OBJECT-TYPE
    SYNTAX DisplayString
    MAX-ACCESS read-write
    STATUS current
    DESCRIPTION
        "High event threshold.  This is a floating point value."
    ::= { acpmTRPEntry 8 }
    --1.3.6.1.4.1.3052.17.2.12.12.5.1.8

acpmTRPHighActions OBJECT-TYPE
    SYNTAX DisplayString
    MAX-ACCESS read-write
    STATUS current
    DESCRIPTION
        "High event actions."
    ::= { acpmTRPEntry 9 }
    --1.3.6.1.4.1.3052.17.2.12.12.5.1.9

acpmTRPHighTrapNum OBJECT-TYPE
    SYNTAX Integer32 (523..1199)
    MAX-ACCESS read-write
    STATUS current
    DESCRIPTION
        "High event trap number."
    ::= { acpmTRPEntry 10 }
    --1.3.6.1.4.1.3052.17.2.12.12.5.1.10

acpmTRPHighClass OBJECT-TYPE
    SYNTAX DisplayString
    MAX-ACCESS read-write
    STATUS current
    DESCRIPTION
        "High event class."
    ::= { acpmTRPEntry 11 }
    --1.3.6.1.4.1.3052.17.2.12.12.5.1.11

acpmTRPNormalActions OBJECT-TYPE
    SYNTAX DisplayString
    MAX-ACCESS read-write
    STATUS current
    DESCRIPTION
        "Return to normal actions."
    ::= { acpmTRPEntry 12 }
    --1.3.6.1.4.1.3052.17.2.12.12.5.1.12

acpmTRPNormalTrapNum OBJECT-TYPE
    SYNTAX Integer32 (523..1199)
    MAX-ACCESS read-write
    STATUS current
    DESCRIPTION
        "Return to normal trap number."
    ::= { acpmTRPEntry 13 }
    --1.3.6.1.4.1.3052.17.2.12.12.5.1.13

acpmTRPNormalClass OBJECT-TYPE
    SYNTAX DisplayString
    MAX-ACCESS read-write
    STATUS current
    DESCRIPTION
        "Return to normal class."
    ::= { acpmTRPEntry 14 }
    --1.3.6.1.4.1.3052.17.2.12.12.5.1.14

acpmTRPLowValue OBJECT-TYPE
    SYNTAX DisplayString
    MAX-ACCESS read-write
    STATUS current
    DESCRIPTION
        "Low event threshold.  This is a floating point value."
    ::= { acpmTRPEntry 15 }
    --1.3.6.1.4.1.3052.17.2.12.12.5.1.15

acpmTRPLowActions OBJECT-TYPE
    SYNTAX DisplayString
    MAX-ACCESS read-write
    STATUS current
    DESCRIPTION
        "Low event actions."
    ::= { acpmTRPEntry 16 }
    --1.3.6.1.4.1.3052.17.2.12.12.5.1.16

acpmTRPLowTrapNum OBJECT-TYPE
    SYNTAX Integer32 (523..1199)
    MAX-ACCESS read-write
    STATUS current
    DESCRIPTION
        "Low event trap number."
    ::= { acpmTRPEntry 17 }
    --1.3.6.1.4.1.3052.17.2.12.12.5.1.17

acpmTRPLowClass OBJECT-TYPE
    SYNTAX DisplayString
    MAX-ACCESS read-write
    STATUS current
    DESCRIPTION
        "Low event class."
    ::= { acpmTRPEntry 18 }
    --1.3.6.1.4.1.3052.17.2.12.12.5.1.18

acpmTRPVLowValue OBJECT-TYPE
    SYNTAX DisplayString
    MAX-ACCESS read-write
    STATUS current
    DESCRIPTION
        "Very low event threshold.  This is a floating point value."
    ::= { acpmTRPEntry 19 }
    --1.3.6.1.4.1.3052.17.2.12.12.5.1.19

acpmTRPVLowActions OBJECT-TYPE
    SYNTAX DisplayString
    MAX-ACCESS read-write
    STATUS current
    DESCRIPTION
        "Very low event actions."
    ::= { acpmTRPEntry 20 }
    --1.3.6.1.4.1.3052.17.2.12.12.5.1.20

acpmTRPVLowTrapNum OBJECT-TYPE
    SYNTAX Integer32 (523..1199)
    MAX-ACCESS read-write
    STATUS current
    DESCRIPTION
        "Very low event trap number."
    ::= { acpmTRPEntry 21 }
    --1.3.6.1.4.1.3052.17.2.12.12.5.1.21

acpmTRPVLowClass OBJECT-TYPE
    SYNTAX DisplayString
    MAX-ACCESS read-write
    STATUS current
    DESCRIPTION
        "Very low event class."
    ::= { acpmTRPEntry 22 }
    --1.3.6.1.4.1.3052.17.2.12.12.5.1.22

acpmTRPSysrepEnable OBJECT-TYPE
    SYNTAX DisplayString
    MAX-ACCESS read-write
    STATUS current
    DESCRIPTION
        "System reporting enable for total real power telemetry."
    ::= { acpmTRPEntry 23 }
    --1.3.6.1.4.1.3052.17.2.12.12.5.1.23

acpmTRPSysrepThreshold OBJECT-TYPE
    SYNTAX DisplayString
    MAX-ACCESS read-write
    STATUS current
    DESCRIPTION
        "System reporting threshold for total real power telemetry.  This is a
        floating point value."
    ::= { acpmTRPEntry 24 }
    --1.3.6.1.4.1.3052.17.2.12.12.5.1.24

acpmTRPSysrepLimit OBJECT-TYPE
    SYNTAX Integer32
    MAX-ACCESS read-write
    STATUS current
    DESCRIPTION
        "System reporting limit for total real power telemetry."
    ::= { acpmTRPEntry 25 }
    --1.3.6.1.4.1.3052.17.2.12.12.5.1.25


acpmDisconnectTable OBJECT-TYPE
    SYNTAX SEQUENCE OF ACPMConfigDisconnect
    MAX-ACCESS not-accessible
    STATUS current
    DESCRIPTION
        "This table organizes AC power monitor device disconnect event
        attributes."
    ::= { acPowerMonitor 6 }
    --1.3.6.1.4.1.3052.17.2.12.12.6

acpmDisconnectEntry OBJECT-TYPE
    SYNTAX ACPMConfigDisconnect
    MAX-ACCESS not-accessible
    STATUS current
    DESCRIPTION
        "Entry for AC power monitor device disconnect event config table."
    INDEX { acpmDisconnectIndex }
    ::= { acpmDisconnectTable 1 }
    --1.3.6.1.4.1.3052.17.2.12.12.6.1

acpmDisconnectIndex OBJECT-TYPE
    SYNTAX Integer32 (1..6)
    MAX-ACCESS read-only
    STATUS current
    DESCRIPTION
        "Which AC power monitor in the AC power monitor device disconnect event
        config table."
    ::= { acpmDisconnectEntry 1 }
    --1.3.6.1.4.1.3052.17.2.12.12.6.1.1

acpmDisconnectEnable OBJECT-TYPE
    SYNTAX DisplayString
    MAX-ACCESS read-write
    STATUS current
    DESCRIPTION
        "Enable AC power monitor device disconnect event."
    ::= { acpmDisconnectEntry 2 }
    --1.3.6.1.4.1.3052.17.2.12.12.6.1.2

acpmDisconnectActions OBJECT-TYPE
    SYNTAX DisplayString
    MAX-ACCESS read-write
    STATUS current
    DESCRIPTION
        "Actions for disconnect event."
    ::= { acpmDisconnectEntry 3 }
    --1.3.6.1.4.1.3052.17.2.12.12.6.1.3

acpmDisconnectTrapNum OBJECT-TYPE
    SYNTAX Integer32 (524..1199)
    MAX-ACCESS read-write
    STATUS current
    DESCRIPTION
        "Trap number for disconnect event."
    ::= { acpmDisconnectEntry 4 }
    --1.3.6.1.4.1.3052.17.2.12.12.6.1.4

acpmDisconnectClass OBJECT-TYPE
    SYNTAX DisplayString
    MAX-ACCESS read-write
    STATUS current
    DESCRIPTION
        "Class for disconnect event."
    ::= { acpmDisconnectEntry 5 }
    --1.3.6.1.4.1.3052.17.2.12.12.6.1.5

acpmDisconnectNormalActions OBJECT-TYPE
    SYNTAX DisplayString
    MAX-ACCESS read-write
    STATUS current
    DESCRIPTION
        "Actions for disconnect return to normal event."
    ::= { acpmDisconnectEntry 6 }
    --1.3.6.1.4.1.3052.17.2.12.12.6.1.6

acpmDisconnectNormalTrapNum OBJECT-TYPE
    SYNTAX Integer32 (524..1199)
    MAX-ACCESS read-write
    STATUS current
    DESCRIPTION
        "Trap number for disconnect return to normal event."
    ::= { acpmDisconnectEntry 7 }
    --1.3.6.1.4.1.3052.17.2.12.12.6.1.7

acpmDisconnectNormalClass OBJECT-TYPE
    SYNTAX DisplayString
    MAX-ACCESS read-write
    STATUS current
    DESCRIPTION
        "Class for disconnect return to normal event."
    ::= { acpmDisconnectEntry 8 }
    --1.3.6.1.4.1.3052.17.2.12.12.6.1.8


acpmTotalPowerFactorTable OBJECT-TYPE
    SYNTAX SEQUENCE OF ACPMConfigTotalPowerFactor
    MAX-ACCESS not-accessible
    STATUS current
    DESCRIPTION
        "This table organizes AC power monitor device total power factor
        event attributes."
    ::= { acPowerMonitor 7 }
    --1.3.6.1.4.1.3052.17.2.12.12.7

acpmTPFEntry OBJECT-TYPE
    SYNTAX ACPMConfigTotalPowerFactor
    MAX-ACCESS not-accessible
    STATUS current
    DESCRIPTION
        "Entry for AC power monitor device total power factor event config
        table."
    INDEX { acpmTPFIndex }
    ::= { acpmTotalPowerFactorTable 1 }
    --1.3.6.1.4.1.3052.17.2.12.12.7.1

acpmTPFIndex OBJECT-TYPE
    SYNTAX Integer32 (1..6)
    MAX-ACCESS read-only
    STATUS current
    DESCRIPTION
        "Which AC power monitor in the AC power monitor device disconnect
        event config table."
    ::= { acpmTPFEntry 1 }
    --1.3.6.1.4.1.3052.17.2.12.12.7.1.1

acpmTPFEnable OBJECT-TYPE
    SYNTAX DisplayString
    MAX-ACCESS read-write
    STATUS current
    DESCRIPTION
        "Enable AC power monitor device disconnect event."
    ::= { acpmTPFEntry 2 }
    --1.3.6.1.4.1.3052.17.2.12.12.7.1.2

acpmTPFDeadband OBJECT-TYPE
    SYNTAX DisplayString
    MAX-ACCESS read-write
    STATUS current
    DESCRIPTION
        "Deadband (hysteresis)."
    ::= { acpmTPFEntry 3 }
    --1.3.6.1.4.1.3052.17.2.12.12.7.1.3

acpmTPFNormalActions OBJECT-TYPE
    SYNTAX DisplayString
    MAX-ACCESS read-write
    STATUS current
    DESCRIPTION
        "Normal actions."
    ::= { acpmTPFEntry 4 }
    --1.3.6.1.4.1.3052.17.2.12.12.7.1.4

acpmTPFNormalTrapNum OBJECT-TYPE
    SYNTAX Integer32
    MAX-ACCESS read-write
    STATUS current
    DESCRIPTION
        "Normal trap number."
    ::= { acpmTPFEntry 5 }
    --1.3.6.1.4.1.3052.17.2.12.12.7.1.5

acpmTPFNormalClass OBJECT-TYPE
    SYNTAX DisplayString
    MAX-ACCESS read-write
    STATUS current
    DESCRIPTION
        "Normal class."
    ::= { acpmTPFEntry 6 }
    --1.3.6.1.4.1.3052.17.2.12.12.7.1.6

acpmTPFLowValue OBJECT-TYPE
    SYNTAX DisplayString
    MAX-ACCESS read-write
    STATUS current
    DESCRIPTION
        "Low threshold."
    ::= { acpmTPFEntry 7 }
    --1.3.6.1.4.1.3052.17.2.12.12.7.1.7

acpmTPFLowActions OBJECT-TYPE
    SYNTAX DisplayString
    MAX-ACCESS read-write
    STATUS current
    DESCRIPTION
        "Low actions."
    ::= { acpmTPFEntry 8 }
    --1.3.6.1.4.1.3052.17.2.12.12.7.1.8

acpmTPFLowTrapNum OBJECT-TYPE
    SYNTAX Integer32
    MAX-ACCESS read-write
    STATUS current
    DESCRIPTION
        "Low trap number."
    ::= { acpmTPFEntry 9 }
    --1.3.6.1.4.1.3052.17.2.12.12.7.1.9

acpmTPFLowClass OBJECT-TYPE
    SYNTAX DisplayString
    MAX-ACCESS read-write
    STATUS current
    DESCRIPTION
        "Low class."
    ::= { acpmTPFEntry 10 }
    --1.3.6.1.4.1.3052.17.2.12.12.7.1.10

acpmTPFVLowValue OBJECT-TYPE
    SYNTAX DisplayString
    MAX-ACCESS read-write
    STATUS current
    DESCRIPTION
        "Very Low threshold."
    ::= { acpmTPFEntry 11 }
    --1.3.6.1.4.1.3052.17.2.12.12.7.1.11

acpmTPFVLowActions OBJECT-TYPE
    SYNTAX DisplayString
    MAX-ACCESS read-write
    STATUS current
    DESCRIPTION
        "Very Low actions."
    ::= { acpmTPFEntry 12 }
    --1.3.6.1.4.1.3052.17.2.12.12.7.1.12

acpmTPFVLowTrapNum OBJECT-TYPE
    SYNTAX Integer32
    MAX-ACCESS read-write
    STATUS current
    DESCRIPTION
        "Very Low trap number."
    ::= { acpmTPFEntry 13 }
    --1.3.6.1.4.1.3052.17.2.12.12.7.1.13

acpmTPFVLowClass OBJECT-TYPE
    SYNTAX DisplayString
    MAX-ACCESS read-write
    STATUS current
    DESCRIPTION
        "Very Low class."
    ::= { acpmTPFEntry 14 }
    --1.3.6.1.4.1.3052.17.2.12.12.7.1.14

acpmTPFSysrepEnable OBJECT-TYPE
    SYNTAX DisplayString
    MAX-ACCESS read-write
    STATUS current
    DESCRIPTION
        "System reporting enable."
    ::= { acpmTPFEntry 15 }
    --1.3.6.1.4.1.3052.17.2.12.12.7.1.15

acpmTPFSysrepThreshold OBJECT-TYPE
    SYNTAX DisplayString
    MAX-ACCESS read-write
    STATUS current
    DESCRIPTION
        "System reporting threshold."
    ::= { acpmTPFEntry 16 }
    --1.3.6.1.4.1.3052.17.2.12.12.7.1.16

acpmTPFSysrepLimit OBJECT-TYPE
    SYNTAX Integer32
    MAX-ACCESS read-write
    STATUS current
    DESCRIPTION
        "System reporting limit."
    ::= { acpmTPFEntry 17 }
    --1.3.6.1.4.1.3052.17.2.12.12.7.1.17


--***************************************************************************************
--Battery Monitor Config Section       2.12.14
--***************************************************************************************

batteryMonitorGeneralTable OBJECT-TYPE
    SYNTAX SEQUENCE OF BatteryMonitorConfigGeneral
    MAX-ACCESS not-accessible
    STATUS current
    DESCRIPTION
        "This table organizes general battery monitor attributes."
    ::= { batteryMonitor 1 }
    --1.3.6.1.4.1.3052.17.2.12.14.1

bmGenEntry OBJECT-TYPE
    SYNTAX BatteryMonitorConfigGeneral
    MAX-ACCESS not-accessible
    STATUS current
    DESCRIPTION
        "Entry for battery monitor general config table."
    INDEX { bmGenIndex }
    ::= { batteryMonitorGeneralTable 1 }
    --1.3.6.1.4.1.3052.17.2.12.14.1.1

bmGenIndex OBJECT-TYPE
    SYNTAX Integer32 (1..9)
    MAX-ACCESS read-only
    STATUS current
    DESCRIPTION
        "Which battery monitor in the battery monitor general config table."
    ::= { bmGenEntry 1 }
    --1.3.6.1.4.1.3052.17.2.12.14.1.1.1

bmGenEnable OBJECT-TYPE
    SYNTAX DisplayString
    MAX-ACCESS read-write
    STATUS current
    DESCRIPTION
        "Which battery monitor in the battery monitor general config table."
    ::= { bmGenEntry 2 }
    --1.3.6.1.4.1.3052.17.2.12.14.1.1.2

bmGenName OBJECT-TYPE
    SYNTAX DisplayString
    MAX-ACCESS read-write
    STATUS current
    DESCRIPTION
        "Name for this battery monitor."
    ::= { bmGenEntry 3 }
    --1.3.6.1.4.1.3052.17.2.12.14.1.1.3

bmGenBatteryQuantity OBJECT-TYPE
    SYNTAX Integer32 (1..4)
    MAX-ACCESS read-write
    STATUS current
    DESCRIPTION
        "Number of batteries in the string."
    ::= { bmGenEntry 4 }
    --1.3.6.1.4.1.3052.17.2.12.14.1.1.4

bmGenBatteryCapacity OBJECT-TYPE
    SYNTAX Integer32 (5..500)
    MAX-ACCESS read-write
    STATUS current
    DESCRIPTION
        "Capacity of the individual batteries in the string, in amp-hours. A
        single value applies to all batteries; that is, they are assumed to be
        all of the same capacity."
    ::= { bmGenEntry 5 }
    --1.3.6.1.4.1.3052.17.2.12.14.1.1.5

bmGenBatteryNominalVoltage OBJECT-TYPE
    SYNTAX DisplayString
    MAX-ACCESS read-write
    STATUS current
    DESCRIPTION
        "Nominal voltage of the individual batteries in the string, in volts.
        A single value applies to all batteres; that is, they are assumed to
        be all of the same voltage.  This is a floating point value."
    ::= { bmGenEntry 6 }
    --1.3.6.1.4.1.3052.17.2.12.14.1.1.6

bmGenSysrepPackage OBJECT-TYPE
    SYNTAX Integer32 (0..10)
    MAX-ACCESS read-write
    STATUS current
    DESCRIPTION
        "System reporting package number."
    ::= { bmGenEntry 7 }
    --1.3.6.1.4.1.3052.17.2.12.14.1.1.7

bmGenSysrepType OBJECT-TYPE
    SYNTAX DisplayString
    MAX-ACCESS read-write
    STATUS current
    DESCRIPTION
        "System reporting ASM profile type."
    ::= { bmGenEntry 8 }
    --1.3.6.1.4.1.3052.17.2.12.14.1.1.8



batteryMonitorDeviceTable OBJECT-TYPE
    SYNTAX SEQUENCE OF BatteryMonitorConfigDevice
    MAX-ACCESS not-accessible
    STATUS current
    DESCRIPTION
        "This table organizes temperature battery monitor attributes."
    ::= { batteryMonitor 2 }
    --1.3.6.1.4.1.3052.17.2.12.14.2

bmDeviceEntry OBJECT-TYPE
    SYNTAX BatteryMonitorConfigDevice
    MAX-ACCESS not-accessible
    STATUS current
    DESCRIPTION
        "Entry for battery monitor temperature config table."
    INDEX { bmDeviceIndex }
    ::= { batteryMonitorDeviceTable 1 }
    --1.3.6.1.4.1.3052.17.2.12.14.2.1

bmDeviceIndex OBJECT-TYPE
    SYNTAX Integer32 (1..9)
    MAX-ACCESS read-only
    STATUS current
    DESCRIPTION
        "Which battery monitor in the battery monitor device config table."
    ::= { bmDeviceEntry 1 }
    --1.3.6.1.4.1.3052.17.2.12.14.2.1.1

bmDeviceType OBJECT-TYPE
    SYNTAX DisplayString
    MAX-ACCESS read-write
    STATUS current
    DESCRIPTION
        "The type of hardware battery monitor unit associated with this battery
        monitor."
    ::= { bmDeviceEntry 2 }
    --1.3.6.1.4.1.3052.17.2.12.14.2.1.2

bmDeviceES OBJECT-TYPE
    SYNTAX Integer32 (1..16)
    MAX-ACCESS read-write
    STATUS current
    DESCRIPTION
        "The ES index of the hardware battery monitor unit associated with this
        battery monitor.   This setting only pertains to the ES-BMU."
    ::= { bmDeviceEntry 3 }
    --1.3.6.1.4.1.3052.17.2.12.14.2.1.3

bmDeviceIP OBJECT-TYPE
    SYNTAX IpAddress
    MAX-ACCESS read-write
    STATUS current
    DESCRIPTION
        "The IP address of the hardware battery monitor unit associated with
        this battery monitor."
    ::= { bmDeviceEntry 4 }
    --1.3.6.1.4.1.3052.17.2.12.14.2.1.4

bmDeviceReadcom OBJECT-TYPE
    SYNTAX DisplayString
    MAX-ACCESS read-write
    STATUS current
    DESCRIPTION
        "The SNMP read community of the hardware battery monitor unit
        associated with this battery monitor."
    ::= { bmDeviceEntry 5 }
    --1.3.6.1.4.1.3052.17.2.12.14.2.1.5

bmDeviceInputString OBJECT-TYPE
    SYNTAX Integer32 (1..3)
    MAX-ACCESS read-write
    STATUS current
    DESCRIPTION
        "Which string on the hardware battery monitor unit is
        associated with this battery monitor. "
    ::= { bmDeviceEntry 6 }
    --1.3.6.1.4.1.3052.17.2.12.14.2.1.6

bmDeviceCTSize OBJECT-TYPE
    SYNTAX Integer32 (0..999)
    MAX-ACCESS read-write
    STATUS current
    DESCRIPTION
        "The rating of the DC current sensor, in amperes.  If this value is set
        to 0, then string current will not be measured. This setting only
        pertains to the ES-BMU."
    ::= { bmDeviceEntry 7 }
    --1.3.6.1.4.1.3052.17.2.12.14.2.1.7

batteryMonitorTempTable OBJECT-TYPE
    SYNTAX SEQUENCE OF BatteryMonitorConfigTemp
    MAX-ACCESS not-accessible
    STATUS current
    DESCRIPTION
        "This table organizes temperature battery monitor attributes."
    ::= { batteryMonitor 3 }
    --1.3.6.1.4.1.3052.17.2.12.14.3

bmTempEntry OBJECT-TYPE
    SYNTAX BatteryMonitorConfigTemp
    MAX-ACCESS not-accessible
    STATUS current
    DESCRIPTION
        "Entry for battery monitor temperature config table."
    INDEX { bmTempIndex }
    ::= { batteryMonitorTempTable 1 }
    --1.3.6.1.4.1.3052.17.2.12.14.3.1

bmTempIndex OBJECT-TYPE
    SYNTAX Integer32 (1..9)
    MAX-ACCESS read-only
    STATUS current
    DESCRIPTION
        "Which battery monitor in the battery monitor temperature config table."
    ::= { bmTempEntry 1 }
    --1.3.6.1.4.1.3052.17.2.12.14.3.1.1

bmTempEnable OBJECT-TYPE
    SYNTAX DisplayString
    MAX-ACCESS read-write
    STATUS current
    DESCRIPTION
        "Enable/disable temperature event.  This event is based on the average
        temperature of the jars in the string."
    ::= { bmTempEntry 2 }
    --1.3.6.1.4.1.3052.17.2.12.14.3.1.2

bmTempDeadband OBJECT-TYPE
    SYNTAX DisplayString
    MAX-ACCESS read-write
    STATUS current
    DESCRIPTION
        "Deadband in degrees F or C, depending on scale setting of sensor
        referenced by bmGenDeviceES.  This is a floating point value."
    ::= { bmTempEntry 3 }
    --1.3.6.1.4.1.3052.17.2.12.14.3.1.3

bmTempScale OBJECT-TYPE
    SYNTAX DisplayString
    MAX-ACCESS read-write
    STATUS current
    DESCRIPTION
        "Temperature scale; this affects how temperature values are
        represented, and also how the temperature alarm thresholds and
        deadbands are interpreted."
    ::= { bmTempEntry 4 }
    --1.3.6.1.4.1.3052.17.2.12.14.3.1.4

bmTempHighValue OBJECT-TYPE
    SYNTAX DisplayString
    MAX-ACCESS read-write
    STATUS current
    DESCRIPTION
        "Very high event threshold in degrees F or C, depending on scale
        setting referenced by bmGenDeviceES.  This is a floating point value."
    ::= { bmTempEntry 5 }
    --1.3.6.1.4.1.3052.17.2.12.14.3.1.5

bmTempHighActions OBJECT-TYPE
    SYNTAX DisplayString
    MAX-ACCESS read-write
    STATUS current
    DESCRIPTION
        "Actions for very high temperature event."
    ::= { bmTempEntry 6 }
    --1.3.6.1.4.1.3052.17.2.12.14.3.1.6

bmTempHighTrapNum OBJECT-TYPE
    SYNTAX Integer32 (530..1199)
    MAX-ACCESS read-write
    STATUS current
    DESCRIPTION
        "Trap number for high temperature event."
    ::= { bmTempEntry 7 }
    --1.3.6.1.4.1.3052.17.2.12.14.3.1.7

bmTempHighClass OBJECT-TYPE
    SYNTAX DisplayString
    MAX-ACCESS read-write
    STATUS current
    DESCRIPTION
        "Class for high temperature event."
    ::= { bmTempEntry 8 }
    --1.3.6.1.4.1.3052.17.2.12.14.3.1.8

bmTempNormalActions OBJECT-TYPE
    SYNTAX DisplayString
    MAX-ACCESS read-write
    STATUS current
    DESCRIPTION
        "Actions for return to normal temperature event."
    ::= { bmTempEntry 9 }
    --1.3.6.1.4.1.3052.17.2.12.14.3.1.9

bmTempNormalTrapNum OBJECT-TYPE
    SYNTAX Integer32 (530..1199)
    MAX-ACCESS read-write
    STATUS current
    DESCRIPTION
        "Trap number for return to normal temperature event."
    ::= { bmTempEntry 10 }
    --1.3.6.1.4.1.3052.17.2.12.14.3.1.10

bmTempNormalClass OBJECT-TYPE
    SYNTAX DisplayString
    MAX-ACCESS read-write
    STATUS current
    DESCRIPTION
        "Class for return to normal temperature event."
    ::= { bmTempEntry 11 }
    --1.3.6.1.4.1.3052.17.2.12.14.3.1.11

bmTempLowValue OBJECT-TYPE
    SYNTAX DisplayString
    MAX-ACCESS read-write
    STATUS current
    DESCRIPTION
        "Low event threshold in degrees F or C, depending on scale setting.
        This is a floating point value."
    ::= { bmTempEntry 12 }
    --1.3.6.1.4.1.3052.17.2.12.14.3.1.12

bmTempLowActions OBJECT-TYPE
    SYNTAX DisplayString
    MAX-ACCESS read-write
    STATUS current
    DESCRIPTION
        "Actions for low temperature event."
    ::= { bmTempEntry 13 }
    --1.3.6.1.4.1.3052.17.2.12.14.3.1.13

bmTempLowTrapNum OBJECT-TYPE
    SYNTAX Integer32 (530..1199)
    MAX-ACCESS read-write
    STATUS current
    DESCRIPTION
        "Trap number for low temperature event."
    ::= { bmTempEntry 14 }
    --1.3.6.1.4.1.3052.17.2.12.14.3.1.14

bmTempLowClass OBJECT-TYPE
    SYNTAX DisplayString
    MAX-ACCESS read-write
    STATUS current
    DESCRIPTION
        "Trap number for low temperature event."
    ::= { bmTempEntry 15 }
    --1.3.6.1.4.1.3052.17.2.12.14.3.1.15

bmTempSysrepEnable OBJECT-TYPE
    SYNTAX DisplayString
    MAX-ACCESS read-write
    STATUS current
    DESCRIPTION
        "System reporting enable for temperature telemetry."
    ::= { bmTempEntry 16 }
    --1.3.6.1.4.1.3052.17.2.12.14.3.1.16

bmTempSysrepThreshold OBJECT-TYPE
    SYNTAX DisplayString
    MAX-ACCESS read-write
    STATUS current
    DESCRIPTION
        "System reporting threshold for temperature telemetry.  This is a
        floating point value."
    ::= { bmTempEntry 17 }
    --1.3.6.1.4.1.3052.17.2.12.14.3.1.17

bmTempSysrepLimit OBJECT-TYPE
    SYNTAX Integer32
    MAX-ACCESS read-write
    STATUS current
    DESCRIPTION
        "System reporting limit for temperature telemetry."
    ::= { bmTempEntry 18 }
    --1.3.6.1.4.1.3052.17.2.12.14.3.1.18


batteryMonitorDiffTempTable OBJECT-TYPE
    SYNTAX SEQUENCE OF BatteryMonitorConfigDiffTemp
    MAX-ACCESS not-accessible
    STATUS current
    DESCRIPTION
        "This table organizes differential temperature battery monitor
        attributes."
    ::= { batteryMonitor 4 }
    --1.3.6.1.4.1.3052.17.2.12.14.4

bmDiffTempEntry OBJECT-TYPE
    SYNTAX BatteryMonitorConfigDiffTemp
    MAX-ACCESS not-accessible
    STATUS current
    DESCRIPTION
        "Entry for battery monitor differential temperature config table."
    INDEX { bmDiffTempIndex }
    ::= { batteryMonitorDiffTempTable 1 }
    --1.3.6.1.4.1.3052.17.2.12.14.4.1

bmDiffTempIndex OBJECT-TYPE
    SYNTAX Integer32 (1..9)
    MAX-ACCESS read-only
    STATUS current
    DESCRIPTION
        "Which battery monitor in the battery monitor differential
        temperature config table."
    ::= { bmDiffTempEntry 1 }
    --1.3.6.1.4.1.3052.17.2.12.14.4.1.1

bmDiffTempEnable OBJECT-TYPE
    SYNTAX DisplayString
    MAX-ACCESS read-write
    STATUS current
    DESCRIPTION
        "Enable/disable differential temperature event.  This event is based on
        the differential between the average temperature of the batteries in
        the string, and ambient temperature (ambient - string temperature)."
    ::= { bmDiffTempEntry 2 }
    --1.3.6.1.4.1.3052.17.2.12.14.4.1.2

bmDiffTempDeadband OBJECT-TYPE
    SYNTAX Integer32
    MAX-ACCESS read-write
    STATUS current
    DESCRIPTION
        "Deadband in degrees F or C, depending on scale setting."
    ::= { bmDiffTempEntry 3 }
    --1.3.6.1.4.1.3052.17.2.12.14.4.1.3

bmDiffTempVHighValue OBJECT-TYPE
    SYNTAX Integer32
    MAX-ACCESS read-write
    STATUS current
    DESCRIPTION
        "Very high event threshold in degrees F or C, depending on scale
        setting."
    ::= { bmDiffTempEntry 4 }
    --1.3.6.1.4.1.3052.17.2.12.14.4.1.4

bmDiffTempVHighActions OBJECT-TYPE
    SYNTAX DisplayString
    MAX-ACCESS read-write
    STATUS current
    DESCRIPTION
        "Actions for very high differential temperature event."
    ::= { bmDiffTempEntry 5 }
    --1.3.6.1.4.1.3052.17.2.12.14.4.1.5

bmDiffTempVHighTrapNum OBJECT-TYPE
    SYNTAX Integer32
    MAX-ACCESS read-write
    STATUS current
    DESCRIPTION
        "Trap number for very high differential temperature event."
    ::= { bmDiffTempEntry 6 }
    --1.3.6.1.4.1.3052.17.2.12.14.4.1.6

bmDiffTempVHighClass OBJECT-TYPE
    SYNTAX DisplayString
    MAX-ACCESS read-write
    STATUS current
    DESCRIPTION
        "Class for very high differential temperature event."
    ::= { bmDiffTempEntry 7 }
    --1.3.6.1.4.1.3052.17.2.12.14.4.1.7

bmDiffTempHighValue OBJECT-TYPE
    SYNTAX Integer32
    MAX-ACCESS read-write
    STATUS current
    DESCRIPTION
        "High event threshold in degrees F or C, depending on scale setting."
    ::= { bmDiffTempEntry 8 }
    --1.3.6.1.4.1.3052.17.2.12.14.4.1.8

bmDiffTempHighActions OBJECT-TYPE
    SYNTAX DisplayString
    MAX-ACCESS read-write
    STATUS current
    DESCRIPTION
        "Actions for high differential temperature event."
    ::= { bmDiffTempEntry 9 }
    --1.3.6.1.4.1.3052.17.2.12.14.4.1.9

bmDiffTempHighTrapNum OBJECT-TYPE
    SYNTAX Integer32
    MAX-ACCESS read-write
    STATUS current
    DESCRIPTION
        "Trap number for high differential temperature event."
    ::= { bmDiffTempEntry 10 }
    --1.3.6.1.4.1.3052.17.2.12.14.4.1.10

bmDiffTempHighClass OBJECT-TYPE
    SYNTAX DisplayString
    MAX-ACCESS read-write
    STATUS current
    DESCRIPTION
        "Class for high differential temperature event."
    ::= { bmDiffTempEntry 11 }
    --1.3.6.1.4.1.3052.17.2.12.14.4.1.11

bmDiffTempNormalActions OBJECT-TYPE
    SYNTAX DisplayString
    MAX-ACCESS read-write
    STATUS current
    DESCRIPTION
        "Actions for return to normal differential temperature event."
    ::= { bmDiffTempEntry 12 }
    --1.3.6.1.4.1.3052.17.2.12.14.4.1.12

bmDiffTempNormalTrapNum OBJECT-TYPE
    SYNTAX Integer32
    MAX-ACCESS read-write
    STATUS current
    DESCRIPTION
        "Trap number for return to normal differential temperature event."
    ::= { bmDiffTempEntry 13 }
    --1.3.6.1.4.1.3052.17.2.12.14.4.1.13

bmDiffTempNormalClass OBJECT-TYPE
    SYNTAX DisplayString
    MAX-ACCESS read-write
    STATUS current
    DESCRIPTION
        "Class for return to normal differential temperature event."
    ::= { bmDiffTempEntry 14 }
    --1.3.6.1.4.1.3052.17.2.12.14.4.1.14

bmDiffTempSysrepEnable OBJECT-TYPE
    SYNTAX DisplayString
    MAX-ACCESS read-write
    STATUS current
    DESCRIPTION
        "System reporting enable for differential temperature telemetry."
    ::= { bmDiffTempEntry 15 }
    --1.3.6.1.4.1.3052.17.2.12.14.4.1.15

bmDiffTempSysrepThreshold OBJECT-TYPE
    SYNTAX Integer32
    MAX-ACCESS read-write
    STATUS current
    DESCRIPTION
        "System reporting threshold for differential temperature telemetry."
    ::= { bmDiffTempEntry 16 }
    --1.3.6.1.4.1.3052.17.2.12.14.4.1.16

bmDiffTempSysrepLimit OBJECT-TYPE
    SYNTAX Integer32
    MAX-ACCESS read-write
    STATUS current
    DESCRIPTION
        "System reporting limit for differential temperature telemetry."
    ::= { bmDiffTempEntry 17 }
    --1.3.6.1.4.1.3052.17.2.12.14.4.1.17


batteryMonitorVoltageTable OBJECT-TYPE
    SYNTAX SEQUENCE OF BatteryMonitorConfigVoltage
    MAX-ACCESS not-accessible
    STATUS current
    DESCRIPTION
        "This table organizes battery monitor voltage attributes."
    ::= { batteryMonitor 5 }
    --1.3.6.1.4.1.3052.17.2.12.14.5

bmVoltageEntry OBJECT-TYPE
    SYNTAX BatteryMonitorConfigVoltage
    MAX-ACCESS not-accessible
    STATUS current
    DESCRIPTION
        "Entry for battery monitor voltage config table."
    INDEX { bmVoltageIndex }
    ::= { batteryMonitorVoltageTable 1 }
    --1.3.6.1.4.1.3052.17.2.12.14.5.1

bmVoltageIndex OBJECT-TYPE
    SYNTAX Integer32 (1..9)
    MAX-ACCESS read-only
    STATUS current
    DESCRIPTION
        "Which battery monitor in the battery monitor voltage config table."
    ::= { bmVoltageEntry 1 }
    --1.3.6.1.4.1.3052.17.2.12.14.5.1.1

bmVoltageEnable OBJECT-TYPE
    SYNTAX DisplayString
    MAX-ACCESS read-write
    STATUS current
    DESCRIPTION
        "Enable/disable voltage event.  This event is based on the total
        voltage output of the batteries in the string."
    ::= { bmVoltageEntry 2 }
    --1.3.6.1.4.1.3052.17.2.12.14.5.1.2

bmVoltageDeadband OBJECT-TYPE
    SYNTAX DisplayString
    MAX-ACCESS read-write
    STATUS current
    DESCRIPTION
        "Deadband in volts.  This is a floating point value."
    ::= { bmVoltageEntry 3 }
    --1.3.6.1.4.1.3052.17.2.12.14.5.1.3

bmVoltageVHighValue OBJECT-TYPE
    SYNTAX DisplayString
    MAX-ACCESS read-write
    STATUS current
    DESCRIPTION
        "Very high event threshold, in volts.  This is a floating point value."
    ::= { bmVoltageEntry 4 }
    --1.3.6.1.4.1.3052.17.2.12.14.5.1.4

bmVoltageVHighActions OBJECT-TYPE
    SYNTAX DisplayString
    MAX-ACCESS read-write
    STATUS current
    DESCRIPTION
        "Actions for very high voltage event."
    ::= { bmVoltageEntry 5 }
    --1.3.6.1.4.1.3052.17.2.12.14.5.1.5

bmVoltageVHighTrapNum OBJECT-TYPE
    SYNTAX Integer32
    MAX-ACCESS read-write
    STATUS current
    DESCRIPTION
        "Trap number for very high voltage event."
    ::= { bmVoltageEntry 6 }
    --1.3.6.1.4.1.3052.17.2.12.14.5.1.6

bmVoltageVHighClass OBJECT-TYPE
    SYNTAX DisplayString
    MAX-ACCESS read-write
    STATUS current
    DESCRIPTION
        "Class for very high voltage event."
    ::= { bmVoltageEntry 7 }
    --1.3.6.1.4.1.3052.17.2.12.14.5.1.7

bmVoltageHighValue OBJECT-TYPE
    SYNTAX DisplayString
    MAX-ACCESS read-write
    STATUS current
    DESCRIPTION
        "High event threshold, in volts.  This is a floating point value."
    ::= { bmVoltageEntry 8 }
    --1.3.6.1.4.1.3052.17.2.12.14.5.1.8

bmVoltageHighActions OBJECT-TYPE
    SYNTAX DisplayString
    MAX-ACCESS read-write
    STATUS current
    DESCRIPTION
        "Actions for high voltage event."
    ::= { bmVoltageEntry 9 }
    --1.3.6.1.4.1.3052.17.2.12.14.5.1.9

bmVoltageHighTrapNum OBJECT-TYPE
    SYNTAX Integer32
    MAX-ACCESS read-write
    STATUS current
    DESCRIPTION
        "Trap number for high voltage event."
    ::= { bmVoltageEntry 10 }
    --1.3.6.1.4.1.3052.17.2.12.14.5.1.10

bmVoltageHighClass OBJECT-TYPE
    SYNTAX DisplayString
    MAX-ACCESS read-write
    STATUS current
    DESCRIPTION
        "Class for high voltage event."
    ::= { bmVoltageEntry 11 }
    --1.3.6.1.4.1.3052.17.2.12.14.5.1.11

bmVoltageNormalActions OBJECT-TYPE
    SYNTAX DisplayString
    MAX-ACCESS read-write
    STATUS current
    DESCRIPTION
        "Actions for return to normal voltage event."
    ::= { bmVoltageEntry 12 }
    --1.3.6.1.4.1.3052.17.2.12.14.5.1.12

bmVoltageNormalTrapNum OBJECT-TYPE
    SYNTAX Integer32
    MAX-ACCESS read-write
    STATUS current
    DESCRIPTION
        "Trap number for return to normal voltage event."
    ::= { bmVoltageEntry 13 }
    --1.3.6.1.4.1.3052.17.2.12.14.5.1.13

bmVoltageNormalClass OBJECT-TYPE
    SYNTAX DisplayString
    MAX-ACCESS read-write
    STATUS current
    DESCRIPTION
        "Class for return to normal voltage event."
    ::= { bmVoltageEntry 14 }
    --1.3.6.1.4.1.3052.17.2.12.14.5.1.14

bmVoltageLowValue OBJECT-TYPE
    SYNTAX DisplayString
    MAX-ACCESS read-write
    STATUS current
    DESCRIPTION
        "Low event threshold, in volts.  This is a floating point value."
    ::= { bmVoltageEntry 15 }
    --1.3.6.1.4.1.3052.17.2.12.14.5.1.15

bmVoltageLowActions OBJECT-TYPE
    SYNTAX DisplayString
    MAX-ACCESS read-write
    STATUS current
    DESCRIPTION
        "Actions for low voltage event."
    ::= { bmVoltageEntry 16 }
    --1.3.6.1.4.1.3052.17.2.12.14.5.1.16

bmVoltageLowTrapNum OBJECT-TYPE
    SYNTAX Integer32
    MAX-ACCESS read-write
    STATUS current
    DESCRIPTION
        "Trap number for low voltage event."
    ::= { bmVoltageEntry 17 }
    --1.3.6.1.4.1.3052.17.2.12.14.5.1.17

bmVoltageLowClass OBJECT-TYPE
    SYNTAX DisplayString
    MAX-ACCESS read-write
    STATUS current
    DESCRIPTION
        "Class for low voltage event."
    ::= { bmVoltageEntry 18 }
    --1.3.6.1.4.1.3052.17.2.12.14.5.1.18

bmVoltageVLowValue OBJECT-TYPE
    SYNTAX DisplayString
    MAX-ACCESS read-write
    STATUS current
    DESCRIPTION
        "Very Low event threshold, in volts.  This is a floating point value."
    ::= { bmVoltageEntry 19 }
    --1.3.6.1.4.1.3052.17.2.12.14.5.1.19

bmVoltageVLowActions OBJECT-TYPE
    SYNTAX DisplayString
    MAX-ACCESS read-write
    STATUS current
    DESCRIPTION
        "Actions for very low voltage event."
    ::= { bmVoltageEntry 20 }
    --1.3.6.1.4.1.3052.17.2.12.14.5.1.20

bmVoltageVLowTrapNum OBJECT-TYPE
    SYNTAX Integer32
    MAX-ACCESS read-write
    STATUS current
    DESCRIPTION
        "Trap number for very low voltage event."
    ::= { bmVoltageEntry 21 }
    --1.3.6.1.4.1.3052.17.2.12.14.5.1.21

bmVoltageVLowClass OBJECT-TYPE
    SYNTAX DisplayString
    MAX-ACCESS read-write
    STATUS current
    DESCRIPTION
        "Class for very low voltage event."
    ::= { bmVoltageEntry 22 }
    --1.3.6.1.4.1.3052.17.2.12.14.5.1.22

bmVoltageSysrepEnable OBJECT-TYPE
    SYNTAX DisplayString
    MAX-ACCESS read-write
    STATUS current
    DESCRIPTION
        "System reporting enable for voltage telemetry."
    ::= { bmVoltageEntry 23 }
    --1.3.6.1.4.1.3052.17.2.12.14.5.1.23

bmVoltageSysrepThreshold OBJECT-TYPE
    SYNTAX DisplayString
    MAX-ACCESS read-write
    STATUS current
    DESCRIPTION
        "System reporting threshold for voltage telemetry.  This is a floating
        point value."
    ::= { bmVoltageEntry 24 }
    --1.3.6.1.4.1.3052.17.2.12.14.5.1.24

bmVoltageSysrepLimit OBJECT-TYPE
    SYNTAX Integer32
    MAX-ACCESS read-write
    STATUS current
    DESCRIPTION
        "System reporting limit for voltage telemetry."
    ::= { bmVoltageEntry 25 }
    --1.3.6.1.4.1.3052.17.2.12.14.5.1.25


batteryMonitorDiffVoltTable OBJECT-TYPE
    SYNTAX SEQUENCE OF BatteryMonitorConfigDiffVolt
    MAX-ACCESS not-accessible
    STATUS current
    DESCRIPTION
        "This table organizes differential voltage battery monitor
        attributes."
    ::= { batteryMonitor 6 }
    --1.3.6.1.4.1.3052.17.2.12.14.6

bmDiffVoltEntry OBJECT-TYPE
    SYNTAX BatteryMonitorConfigDiffVolt
    MAX-ACCESS not-accessible
    STATUS current
    DESCRIPTION
        "Entry for battery monitor differential voltage config table."
    INDEX { bmDiffVoltIndex }
    ::= { batteryMonitorDiffVoltTable 1 }
    --1.3.6.1.4.1.3052.17.2.12.14.6.1

bmDiffVoltIndex OBJECT-TYPE
    SYNTAX Integer32 (1..9)
    MAX-ACCESS read-only
    STATUS current
    DESCRIPTION
        "Which battery monitor in the battery monitor differential
        voltage config table."
    ::= { bmDiffVoltEntry 1 }
    --1.3.6.1.4.1.3052.17.2.12.14.6.1.1

bmDiffVoltEnable OBJECT-TYPE
    SYNTAX DisplayString
    MAX-ACCESS read-write
    STATUS current
    DESCRIPTION
        "Enable/disable differential voltage event.  This event is based on
        the differential between the highest and lowest jar voltages within
        the string."
    ::= { bmDiffVoltEntry 2 }
    --1.3.6.1.4.1.3052.17.2.12.14.6.1.2

bmDiffVoltDeadband OBJECT-TYPE
    SYNTAX DisplayString
    MAX-ACCESS read-write
    STATUS current
    DESCRIPTION
        "Deadband in volts."
    ::= { bmDiffVoltEntry 3 }
    --1.3.6.1.4.1.3052.17.2.12.14.6.1.3

bmDiffVoltVHighValue OBJECT-TYPE
    SYNTAX DisplayString
    MAX-ACCESS read-write
    STATUS current
    DESCRIPTION
        "Very high event threshold in volts.  This is a floating point value."
    ::= { bmDiffVoltEntry 4 }
    --1.3.6.1.4.1.3052.17.2.12.14.6.1.4

bmDiffVoltVHighActions OBJECT-TYPE
    SYNTAX DisplayString
    MAX-ACCESS read-write
    STATUS current
    DESCRIPTION
        "Actions for very high differential voltage event."
    ::= { bmDiffVoltEntry 5 }
    --1.3.6.1.4.1.3052.17.2.12.14.6.1.5

bmDiffVoltVHighTrapNum OBJECT-TYPE
    SYNTAX Integer32
    MAX-ACCESS read-write
    STATUS current
    DESCRIPTION
        "Trap number for very high differential voltage event."
    ::= { bmDiffVoltEntry 6 }
    --1.3.6.1.4.1.3052.17.2.12.14.6.1.6

bmDiffVoltVHighClass OBJECT-TYPE
    SYNTAX DisplayString
    MAX-ACCESS read-write
    STATUS current
    DESCRIPTION
        "Class for very high differential voltage event."
    ::= { bmDiffVoltEntry 7 }
    --1.3.6.1.4.1.3052.17.2.12.14.6.1.7

bmDiffVoltHighValue OBJECT-TYPE
    SYNTAX DisplayString
    MAX-ACCESS read-write
    STATUS current
    DESCRIPTION
        "High event threshold in volts.  This is a floating point value."
    ::= { bmDiffVoltEntry 8 }
    --1.3.6.1.4.1.3052.17.2.12.14.6.1.8

bmDiffVoltHighActions OBJECT-TYPE
    SYNTAX DisplayString
    MAX-ACCESS read-write
    STATUS current
    DESCRIPTION
        "Actions for high differential voltage event."
    ::= { bmDiffVoltEntry 9 }
    --1.3.6.1.4.1.3052.17.2.12.14.6.1.9

bmDiffVoltHighTrapNum OBJECT-TYPE
    SYNTAX Integer32
    MAX-ACCESS read-write
    STATUS current
    DESCRIPTION
        "Trap number for high differential voltage event."
    ::= { bmDiffVoltEntry 10 }
    --1.3.6.1.4.1.3052.17.2.12.14.6.1.10

bmDiffVoltHighClass OBJECT-TYPE
    SYNTAX DisplayString
    MAX-ACCESS read-write
    STATUS current
    DESCRIPTION
        "Class for high differential voltage event."
    ::= { bmDiffVoltEntry 11 }
    --1.3.6.1.4.1.3052.17.2.12.14.6.1.11

bmDiffVoltNormalActions OBJECT-TYPE
    SYNTAX DisplayString
    MAX-ACCESS read-write
    STATUS current
    DESCRIPTION
        "Actions for return to normal differential voltage event."
    ::= { bmDiffVoltEntry 12 }
    --1.3.6.1.4.1.3052.17.2.12.14.6.1.12

bmDiffVoltNormalTrapNum OBJECT-TYPE
    SYNTAX Integer32
    MAX-ACCESS read-write
    STATUS current
    DESCRIPTION
        "Trap number for return to normal differential voltage event."
    ::= { bmDiffVoltEntry 13 }
    --1.3.6.1.4.1.3052.17.2.12.14.6.1.13

bmDiffVoltNormalClass OBJECT-TYPE
    SYNTAX DisplayString
    MAX-ACCESS read-write
    STATUS current
    DESCRIPTION
        "Class for return to normal differential voltage event."
    ::= { bmDiffVoltEntry 14 }
    --1.3.6.1.4.1.3052.17.2.12.14.6.1.14

bmDiffVoltSysrepEnable OBJECT-TYPE
    SYNTAX DisplayString
    MAX-ACCESS read-write
    STATUS current
    DESCRIPTION
        "System reporting enable for differential voltage telemetry."
    ::= { bmDiffVoltEntry 15 }
    --1.3.6.1.4.1.3052.17.2.12.14.6.1.15

bmDiffVoltSysrepThreshold OBJECT-TYPE
    SYNTAX DisplayString
    MAX-ACCESS read-write
    STATUS current
    DESCRIPTION
        "System reporting threshold for differential voltage telemetry."
    ::= { bmDiffVoltEntry 16 }
    --1.3.6.1.4.1.3052.17.2.12.14.6.1.16

bmDiffVoltSysrepLimit OBJECT-TYPE
    SYNTAX Integer32
    MAX-ACCESS read-write
    STATUS current
    DESCRIPTION
        "System reporting limit for differential voltage telemetry."
    ::= { bmDiffVoltEntry 17 }
    --1.3.6.1.4.1.3052.17.2.12.14.6.1.17


batteryMonitorChargingCurrentTable OBJECT-TYPE
    SYNTAX SEQUENCE OF BatteryMonitorConfigChargingCurrent
    MAX-ACCESS not-accessible
    STATUS current
    DESCRIPTION
        "This table organizes battery monitor charging current attributes."
    ::= { batteryMonitor 7 }
    --1.3.6.1.4.1.3052.17.2.12.14.7

bmChargingCurrentEntry OBJECT-TYPE
    SYNTAX BatteryMonitorConfigChargingCurrent
    MAX-ACCESS not-accessible
    STATUS current
    DESCRIPTION
        "Entry for battery monitor differential charging current config table."
    INDEX { bmChargingCurrentIndex }
    ::= { batteryMonitorChargingCurrentTable 1 }
    --1.3.6.1.4.1.3052.17.2.12.14.7.1

bmChargingCurrentIndex OBJECT-TYPE
    SYNTAX Integer32 (1..9)
    MAX-ACCESS read-only
    STATUS current
    DESCRIPTION
        "Which battery monitor in the battery monitor charging current config table."
    ::= { bmChargingCurrentEntry 1 }
    --1.3.6.1.4.1.3052.17.2.12.14.7.1.1

bmChargingCurrentEnable OBJECT-TYPE
    SYNTAX DisplayString
    MAX-ACCESS read-write
    STATUS current
    DESCRIPTION
        "Enable/disable charging current event.  This event is based on
        positive current flow (i.e. current flowing into the battery string)."
    ::= { bmChargingCurrentEntry 2 }
    --1.3.6.1.4.1.3052.17.2.12.14.7.1.2

bmChargingCurrentDeadband OBJECT-TYPE
    SYNTAX DisplayString
    MAX-ACCESS read-write
    STATUS current
    DESCRIPTION
        "Deadband in amperes.  This is a floating point value."
    ::= { bmChargingCurrentEntry 3 }
    --1.3.6.1.4.1.3052.17.2.12.14.7.1.3

bmChargingCurrentVHighValue OBJECT-TYPE
    SYNTAX DisplayString
    MAX-ACCESS read-write
    STATUS current
    DESCRIPTION
        "Very high event threshold, in volts.  This is a floating point value."
    ::= { bmChargingCurrentEntry 4 }
    --1.3.6.1.4.1.3052.17.2.12.14.7.1.4

bmChargingCurrentVHighActions OBJECT-TYPE
    SYNTAX DisplayString
    MAX-ACCESS read-write
    STATUS current
    DESCRIPTION
        "Actions for very high charging current event."
    ::= { bmChargingCurrentEntry 5 }
    --1.3.6.1.4.1.3052.17.2.12.14.7.1.5

bmChargingCurrentVHighTrapNum OBJECT-TYPE
    SYNTAX Integer32
    MAX-ACCESS read-write
    STATUS current
    DESCRIPTION
        "Trap number for very high charging current event."
    ::= { bmChargingCurrentEntry 6 }
    --1.3.6.1.4.1.3052.17.2.12.14.7.1.6

bmChargingCurrentVHighClass OBJECT-TYPE
    SYNTAX DisplayString
    MAX-ACCESS read-write
    STATUS current
    DESCRIPTION
        "Class for very high charging current event."
    ::= { bmChargingCurrentEntry 7 }
    --1.3.6.1.4.1.3052.17.2.12.14.7.1.7

bmChargingCurrentHighValue OBJECT-TYPE
    SYNTAX DisplayString
    MAX-ACCESS read-write
    STATUS current
    DESCRIPTION
        "High event threshold, in volts.  This is a floating point value."
    ::= { bmChargingCurrentEntry 8 }
    --1.3.6.1.4.1.3052.17.2.12.14.7.1.8

bmChargingCurrentHighActions OBJECT-TYPE
    SYNTAX DisplayString
    MAX-ACCESS read-write
    STATUS current
    DESCRIPTION
        "Actions for high charging current event."
    ::= { bmChargingCurrentEntry 9 }
    --1.3.6.1.4.1.3052.17.2.12.14.7.1.9

bmChargingCurrentHighTrapNum OBJECT-TYPE
    SYNTAX Integer32
    MAX-ACCESS read-write
    STATUS current
    DESCRIPTION
        "Trap number for high charging current event."
    ::= { bmChargingCurrentEntry 10 }
    --1.3.6.1.4.1.3052.17.2.12.14.7.1.10

bmChargingCurrentHighClass OBJECT-TYPE
    SYNTAX DisplayString
    MAX-ACCESS read-write
    STATUS current
    DESCRIPTION
        "Class for high charging current event."
    ::= { bmChargingCurrentEntry 11 }
    --1.3.6.1.4.1.3052.17.2.12.14.7.1.11

bmChargingCurrentNormalActions OBJECT-TYPE
    SYNTAX DisplayString
    MAX-ACCESS read-write
    STATUS current
    DESCRIPTION
        "Actions for return to normal charging current event."
    ::= { bmChargingCurrentEntry 12 }
    --1.3.6.1.4.1.3052.17.2.12.14.7.1.12

bmChargingCurrentNormalTrapNum OBJECT-TYPE
    SYNTAX Integer32
    MAX-ACCESS read-write
    STATUS current
    DESCRIPTION
        "Trap number for return to normal charging current event."
    ::= { bmChargingCurrentEntry 13 }
    --1.3.6.1.4.1.3052.17.2.12.14.7.1.13

bmChargingCurrentNormalClass OBJECT-TYPE
    SYNTAX DisplayString
    MAX-ACCESS read-write
    STATUS current
    DESCRIPTION
        "Class for return to normal charging current event."
    ::= { bmChargingCurrentEntry 14 }
    --1.3.6.1.4.1.3052.17.2.12.14.7.1.14

bmChargingCurrentSysrepEnable OBJECT-TYPE
    SYNTAX DisplayString
    MAX-ACCESS read-write
    STATUS current
    DESCRIPTION
        "System reporting enable for charging current telemetry."
    ::= { bmChargingCurrentEntry 15 }
    --1.3.6.1.4.1.3052.17.2.12.14.7.1.15

bmChargingCurrentSysrepThreshold OBJECT-TYPE
    SYNTAX DisplayString
    MAX-ACCESS read-write
    STATUS current
    DESCRIPTION
        "System reporting threshold for charging current telemetry.  This is a
        floating point value."
    ::= { bmChargingCurrentEntry 16 }
    --1.3.6.1.4.1.3052.17.2.12.14.7.1.16

bmChargingCurrentSysrepLimit OBJECT-TYPE
    SYNTAX Integer32
    MAX-ACCESS read-write
    STATUS current
    DESCRIPTION
        "System reporting limit for charging current telemetry."
    ::= { bmChargingCurrentEntry 17 }
    --1.3.6.1.4.1.3052.17.2.12.14.7.1.17


batteryMonitorDischargingCurrentTable OBJECT-TYPE
    SYNTAX SEQUENCE OF BatteryMonitorConfigDischargingCurrent
    MAX-ACCESS not-accessible
    STATUS current
    DESCRIPTION
        "This table organizes battery monitor discharging current attributes."
    ::= { batteryMonitor 8 }
    --1.3.6.1.4.1.3052.17.2.12.14.8

bmDischargingCurrentEntry OBJECT-TYPE
    SYNTAX BatteryMonitorConfigDischargingCurrent
    MAX-ACCESS not-accessible
    STATUS current
    DESCRIPTION
        "Entry for battery monitor differential discharging current config
        table."
    INDEX { bmDischargingCurrentIndex }
    ::= { batteryMonitorDischargingCurrentTable 1 }
    --1.3.6.1.4.1.3052.17.2.12.14.8.1

bmDischargingCurrentIndex OBJECT-TYPE
    SYNTAX Integer32 (1..9)
    MAX-ACCESS read-only
    STATUS current
    DESCRIPTION
        "Which battery monitor in the battery monitor discharging current
        config table."
    ::= { bmDischargingCurrentEntry 1 }
    --1.3.6.1.4.1.3052.17.2.12.14.8.1.1

bmDischargingCurrentEnable OBJECT-TYPE
    SYNTAX DisplayString
    MAX-ACCESS read-write
    STATUS current
    DESCRIPTION
        "Enable/disable discharging current event.  This event is based on
        positive current flow (i.e. current flowing into the battery string)."
    ::= { bmDischargingCurrentEntry 2 }
    --1.3.6.1.4.1.3052.17.2.12.14.8.1.2

bmDischargingCurrentDeadband OBJECT-TYPE
    SYNTAX DisplayString
    MAX-ACCESS read-write
    STATUS current
    DESCRIPTION
        "Deadband in amperes.  This is a floating point value."
    ::= { bmDischargingCurrentEntry 3 }
    --1.3.6.1.4.1.3052.17.2.12.14.8.1.3

bmDischargingCurrentVHighValue OBJECT-TYPE
    SYNTAX DisplayString
    MAX-ACCESS read-write
    STATUS current
    DESCRIPTION
        "Very high event threshold, in volts.  This is a floating point value."
    ::= { bmDischargingCurrentEntry 4 }
    --1.3.6.1.4.1.3052.17.2.12.14.8.1.4

bmDischargingCurrentVHighActions OBJECT-TYPE
    SYNTAX DisplayString
    MAX-ACCESS read-write
    STATUS current
    DESCRIPTION
        "Actions for very high discharging current event."
    ::= { bmDischargingCurrentEntry 5 }
    --1.3.6.1.4.1.3052.17.2.12.14.8.1.5

bmDischargingCurrentVHighTrapNum OBJECT-TYPE
    SYNTAX Integer32
    MAX-ACCESS read-write
    STATUS current
    DESCRIPTION
        "Trap number for very high discharging current event."
    ::= { bmDischargingCurrentEntry 6 }
    --1.3.6.1.4.1.3052.17.2.12.14.8.1.6

bmDischargingCurrentVHighClass OBJECT-TYPE
    SYNTAX DisplayString
    MAX-ACCESS read-write
    STATUS current
    DESCRIPTION
        "Class for very high discharging current event."
    ::= { bmDischargingCurrentEntry 7 }
    --1.3.6.1.4.1.3052.17.2.12.14.8.1.7

bmDischargingCurrentHighValue OBJECT-TYPE
    SYNTAX DisplayString
    MAX-ACCESS read-write
    STATUS current
    DESCRIPTION
        "High event threshold, in volts.  This is a floating point value."
    ::= { bmDischargingCurrentEntry 8 }
    --1.3.6.1.4.1.3052.17.2.12.14.8.1.8

bmDischargingCurrentHighActions OBJECT-TYPE
    SYNTAX DisplayString
    MAX-ACCESS read-write
    STATUS current
    DESCRIPTION
        "Actions for high discharging current event."
    ::= { bmDischargingCurrentEntry 9 }
    --1.3.6.1.4.1.3052.17.2.12.14.8.1.9

bmDischargingCurrentHighTrapNum OBJECT-TYPE
    SYNTAX Integer32
    MAX-ACCESS read-write
    STATUS current
    DESCRIPTION
        "Trap number for high discharging current event."
    ::= { bmDischargingCurrentEntry 10 }
    --1.3.6.1.4.1.3052.17.2.12.14.8.1.10

bmDischargingCurrentHighClass OBJECT-TYPE
    SYNTAX DisplayString
    MAX-ACCESS read-write
    STATUS current
    DESCRIPTION
        "Class for high discharging current event."
    ::= { bmDischargingCurrentEntry 11 }
    --1.3.6.1.4.1.3052.17.2.12.14.8.1.11

bmDischargingCurrentNormalActions OBJECT-TYPE
    SYNTAX DisplayString
    MAX-ACCESS read-write
    STATUS current
    DESCRIPTION
        "Actions for return to normal discharging current event."
    ::= { bmDischargingCurrentEntry 12 }
    --1.3.6.1.4.1.3052.17.2.12.14.8.1.12

bmDischargingCurrentNormalTrapNum OBJECT-TYPE
    SYNTAX Integer32
    MAX-ACCESS read-write
    STATUS current
    DESCRIPTION
        "Trap number for return to normal discharging current event."
    ::= { bmDischargingCurrentEntry 13 }
    --1.3.6.1.4.1.3052.17.2.12.14.8.1.13

bmDischargingCurrentNormalClass OBJECT-TYPE
    SYNTAX DisplayString
    MAX-ACCESS read-write
    STATUS current
    DESCRIPTION
        "Class for return to normal discharging current event."
    ::= { bmDischargingCurrentEntry 14 }
    --1.3.6.1.4.1.3052.17.2.12.14.8.1.14

bmDischargingCurrentSysrepEnable OBJECT-TYPE
    SYNTAX DisplayString
    MAX-ACCESS read-write
    STATUS current
    DESCRIPTION
        "System reporting enable for discharging current telemetry."
    ::= { bmDischargingCurrentEntry 15 }
    --1.3.6.1.4.1.3052.17.2.12.14.8.1.15

bmDischargingCurrentSysrepThreshold OBJECT-TYPE
    SYNTAX DisplayString
    MAX-ACCESS read-write
    STATUS current
    DESCRIPTION
        "System reporting threshold for discharging current telemetry.  This is
        a floating point value."
    ::= { bmDischargingCurrentEntry 16 }
    --1.3.6.1.4.1.3052.17.2.12.14.8.1.16

bmDischargingCurrentSysrepLimit OBJECT-TYPE
    SYNTAX Integer32
    MAX-ACCESS read-write
    STATUS current
    DESCRIPTION
        "System reporting limit for discharging current telemetry."
    ::= { bmDischargingCurrentEntry 17 }
    --1.3.6.1.4.1.3052.17.2.12.14.8.1.17


batteryMonitorChargeLevelTable OBJECT-TYPE
    SYNTAX SEQUENCE OF BatteryMonitorConfigChargeLevel
    MAX-ACCESS not-accessible
    STATUS current
    DESCRIPTION
        "This table organizes battery monitor charge level attributes."
    ::= { batteryMonitor 9 }
    --1.3.6.1.4.1.3052.17.2.12.14.9

bmChargeLevelEntry OBJECT-TYPE
    SYNTAX BatteryMonitorConfigChargeLevel
    MAX-ACCESS not-accessible
    STATUS current
    DESCRIPTION
        "Entry for battery monitor charge level config table."
    INDEX { bmChargeLevelIndex }
    ::= { batteryMonitorChargeLevelTable 1 }
    --1.3.6.1.4.1.3052.17.2.12.14.9.1

bmChargeLevelIndex OBJECT-TYPE
    SYNTAX Integer32 (1..9)
    MAX-ACCESS read-only
    STATUS current
    DESCRIPTION
        "Which battery monitor in the battery monitor charge level config table."
    ::= { bmChargeLevelEntry 1 }
    --1.3.6.1.4.1.3052.17.2.12.14.9.1.1

bmChargeLevelEnable OBJECT-TYPE
    SYNTAX DisplayString
    MAX-ACCESS read-write
    STATUS current
    DESCRIPTION
        "Enable/disable charge level event."
    ::= { bmChargeLevelEntry 2 }
    --1.3.6.1.4.1.3052.17.2.12.14.9.1.2

bmChargeLevelNormalActions OBJECT-TYPE
    SYNTAX DisplayString
    MAX-ACCESS read-write
    STATUS current
    DESCRIPTION
        "Actions for return to normal charge level event."
    ::= { bmChargeLevelEntry 3 }
    --1.3.6.1.4.1.3052.17.2.12.14.9.1.3

bmChargeLevelNormalTrapNum OBJECT-TYPE
    SYNTAX Integer32
    MAX-ACCESS read-write
    STATUS current
    DESCRIPTION
        "Trap number for return to normal charge level event."
    ::= { bmChargeLevelEntry 4 }
    --1.3.6.1.4.1.3052.17.2.12.14.9.1.4

bmChargeLevelNormalClass OBJECT-TYPE
    SYNTAX DisplayString
    MAX-ACCESS read-write
    STATUS current
    DESCRIPTION
        "Class for return to normal charge level event."
    ::= { bmChargeLevelEntry 5 }
    --1.3.6.1.4.1.3052.17.2.12.14.9.1.5

bmChargeLevelLowActions OBJECT-TYPE
    SYNTAX DisplayString
    MAX-ACCESS read-write
    STATUS current
    DESCRIPTION
        "Actions for low charge level event."
    ::= { bmChargeLevelEntry 6 }
    --1.3.6.1.4.1.3052.17.2.12.14.9.1.6

bmChargeLevelLowTrapNum OBJECT-TYPE
    SYNTAX Integer32
    MAX-ACCESS read-write
    STATUS current
    DESCRIPTION
        "Trap number for low charge level event."
    ::= { bmChargeLevelEntry 7 }
    --1.3.6.1.4.1.3052.17.2.12.14.9.1.7

bmChargeLevelLowClass OBJECT-TYPE
    SYNTAX DisplayString
    MAX-ACCESS read-write
    STATUS current
    DESCRIPTION
        "Class for low charge level event."
    ::= { bmChargeLevelEntry 8 }
    --1.3.6.1.4.1.3052.17.2.12.14.9.1.8

bmChargeLevelVLowActions OBJECT-TYPE
    SYNTAX DisplayString
    MAX-ACCESS read-write
    STATUS current
    DESCRIPTION
        "Actions for very low charge level event."
    ::= { bmChargeLevelEntry 9 }
    --1.3.6.1.4.1.3052.17.2.12.14.9.1.9

bmChargeLevelVLowTrapNum OBJECT-TYPE
    SYNTAX Integer32
    MAX-ACCESS read-write
    STATUS current
    DESCRIPTION
        "Trap number for very low charge level event."
    ::= { bmChargeLevelEntry 10 }
    --1.3.6.1.4.1.3052.17.2.12.14.9.1.10

bmChargeLevelVLowClass OBJECT-TYPE
    SYNTAX DisplayString
    MAX-ACCESS read-write
    STATUS current
    DESCRIPTION
        "Class for very low charge level event."
    ::= { bmChargeLevelEntry 11 }
    --1.3.6.1.4.1.3052.17.2.12.14.9.1.11

bmChargeLevelSysrepEnable OBJECT-TYPE
    SYNTAX DisplayString
    MAX-ACCESS read-write
    STATUS current
    DESCRIPTION
        "System reporting enable for charge level telemetry."
    ::= { bmChargeLevelEntry 12 }
    --1.3.6.1.4.1.3052.17.2.12.14.9.1.12


batteryMonitorJarHealthTable OBJECT-TYPE
    SYNTAX SEQUENCE OF BatteryMonitorConfigJarHealth
    MAX-ACCESS not-accessible
    STATUS current
    DESCRIPTION
        "This table organizes battery monitor jar health attributes."
    ::= { batteryMonitor 10 }
    --1.3.6.1.4.1.3052.17.2.12.14.10

bmJarHealthEntry OBJECT-TYPE
    SYNTAX BatteryMonitorConfigJarHealth
    MAX-ACCESS not-accessible
    STATUS current
    DESCRIPTION
        "Entry for battery monitor jar health config table."
    INDEX { bmJarHealthIndex }
    ::= { batteryMonitorJarHealthTable 1 }
    --1.3.6.1.4.1.3052.17.2.12.14.10.1

bmJarHealthIndex OBJECT-TYPE
    SYNTAX Integer32 (1..9)
    MAX-ACCESS read-only
    STATUS current
    DESCRIPTION
        "Which battery monitor in the battery monitor jar health config table."
    ::= { bmJarHealthEntry 1 }
    --1.3.6.1.4.1.3052.17.2.12.14.10.1.1

bmJarHealthEnable OBJECT-TYPE
    SYNTAX DisplayString
    MAX-ACCESS read-write
    STATUS current
    DESCRIPTION
        "Enable/disable jar health event."
    ::= { bmJarHealthEntry 2 }
    --1.3.6.1.4.1.3052.17.2.12.14.10.1.2

bmJarHealthNormalActions OBJECT-TYPE
    SYNTAX DisplayString
    MAX-ACCESS read-write
    STATUS current
    DESCRIPTION
        "Actions for return to normal jar health event."
    ::= { bmJarHealthEntry 3 }
    --1.3.6.1.4.1.3052.17.2.12.14.10.1.3

bmJarHealthNormalTrapNum OBJECT-TYPE
    SYNTAX Integer32
    MAX-ACCESS read-write
    STATUS current
    DESCRIPTION
        "Trap number for return to normal jar health event."
    ::= { bmJarHealthEntry 4 }
    --1.3.6.1.4.1.3052.17.2.12.14.10.1.4

bmJarHealthNormalClass OBJECT-TYPE
    SYNTAX DisplayString
    MAX-ACCESS read-write
    STATUS current
    DESCRIPTION
        "Class for return to normal jar health event."
    ::= { bmJarHealthEntry 5 }
    --1.3.6.1.4.1.3052.17.2.12.14.10.1.5

bmJarHealthLowActions OBJECT-TYPE
    SYNTAX DisplayString
    MAX-ACCESS read-write
    STATUS current
    DESCRIPTION
        "Actions for low jar health event."
    ::= { bmJarHealthEntry 6 }
    --1.3.6.1.4.1.3052.17.2.12.14.10.1.6

bmJarHealthLowTrapNum OBJECT-TYPE
    SYNTAX Integer32
    MAX-ACCESS read-write
    STATUS current
    DESCRIPTION
        "Trap number for low jar health event."
    ::= { bmJarHealthEntry 7 }
    --1.3.6.1.4.1.3052.17.2.12.14.10.1.7

bmJarHealthLowClass OBJECT-TYPE
    SYNTAX DisplayString
    MAX-ACCESS read-write
    STATUS current
    DESCRIPTION
        "Class for low jar health event."
    ::= { bmJarHealthEntry 8 }
    --1.3.6.1.4.1.3052.17.2.12.14.10.1.8

bmJarHealthVLowActions OBJECT-TYPE
    SYNTAX DisplayString
    MAX-ACCESS read-write
    STATUS current
    DESCRIPTION
        "Actions for very low jar health event."
    ::= { bmJarHealthEntry 9 }
    --1.3.6.1.4.1.3052.17.2.12.14.10.1.9

bmJarHealthVLowTrapNum OBJECT-TYPE
    SYNTAX Integer32
    MAX-ACCESS read-write
    STATUS current
    DESCRIPTION
        "Trap number for very low jar health event."
    ::= { bmJarHealthEntry 10 }
    --1.3.6.1.4.1.3052.17.2.12.14.10.1.10

bmJarHealthVLowClass OBJECT-TYPE
    SYNTAX DisplayString
    MAX-ACCESS read-write
    STATUS current
    DESCRIPTION
        "Class for very low jar health event."
    ::= { bmJarHealthEntry 11 }
    --1.3.6.1.4.1.3052.17.2.12.14.10.1.11

bmJarHealthSysrepEnable OBJECT-TYPE
    SYNTAX DisplayString
    MAX-ACCESS read-write
    STATUS current
    DESCRIPTION
        "System reporting enable for jar health telemetry."
    ::= { bmJarHealthEntry 12 }
    --1.3.6.1.4.1.3052.17.2.12.14.10.1.12


--***************************************************************************************
--Reset Event Section   2.12.16
--***************************************************************************************


evResetEnable OBJECT-TYPE
    SYNTAX DisplayString
    MAX-ACCESS read-write
    STATUS current
    DESCRIPTION
        "Enable/disable reset event.  This event is triggered when the unit
        finishes booting."
    ::= { evReset 1 }
    --1.3.6.1.4.1.3052.17.2.12.16.1

evResetDelay OBJECT-TYPE
    SYNTAX Integer32 (0..3600)
    MAX-ACCESS read-write
    STATUS current
    DESCRIPTION
        "Number of seconds to wait after unit finishes booting before triggering
        the reset event."
    ::= { evReset 2 }
    --1.3.6.1.4.1.3052.17.2.12.16.2

evResetActions OBJECT-TYPE
    SYNTAX DisplayString
    MAX-ACCESS read-write
    STATUS current
    DESCRIPTION
        "Actions for reset event."
    ::= { evReset 3 }
    --1.3.6.1.4.1.3052.17.2.12.16.3

evResetMessage OBJECT-TYPE
    SYNTAX DisplayString
    MAX-ACCESS read-write
    STATUS current
    DESCRIPTION
        "Message for reset event."
    ::= { evReset 4 }
    --1.3.6.1.4.1.3052.17.2.12.16.4

evResetTrapnum OBJECT-TYPE
    SYNTAX Integer32 (543..1199)
    MAX-ACCESS read-write
    STATUS current
    DESCRIPTION
        "Trap number for reset event."
    ::= { evReset 5 }
    --1.3.6.1.4.1.3052.17.2.12.16.5

evResetClass OBJECT-TYPE
    SYNTAX DisplayString
    MAX-ACCESS read-write
    STATUS current
    DESCRIPTION
        "Class (severity) for reset event."
    ::= { evReset 6 }
    --1.3.6.1.4.1.3052.17.2.12.16.6


--***************************************************************************************
--Global Event Section   2.12.18
--***************************************************************************************

evGlobalActions OBJECT-TYPE
    SYNTAX DisplayString
    MAX-ACCESS read-write
    STATUS current
    DESCRIPTION
        "Global event actions."
    ::= { evGlobal 2 }
    --1.3.6.1.4.1.3052.17.2.12.18.2

evGlobalTrapnum OBJECT-TYPE
    SYNTAX Integer32 (0..1199)
    MAX-ACCESS read-write
    STATUS current
    DESCRIPTION
        "Global trap number."
    ::= { evGlobal 3 }
    --1.3.6.1.4.1.3052.17.2.12.18.3


--***************************************************************************************
--Action Section   2.14
--***************************************************************************************



actionSchedEnable OBJECT-TYPE
    SYNTAX DisplayString
    MAX-ACCESS read-write
    STATUS current
    DESCRIPTION
        "ON/OFF enable action schedule"
    ::= { actionSched 1 }
    --1.3.6.1.4.1.3052.17.2.14.3.1

actionSchedBegin OBJECT-TYPE
    SYNTAX DisplayString
    MAX-ACCESS read-write
    STATUS current
    DESCRIPTION
        "action schedule begin time (HH:MM)"
    ::= { actionSched 2 }
    --1.3.6.1.4.1.3052.17.2.14.3.2

actionSchedEnd OBJECT-TYPE
    SYNTAX DisplayString
    MAX-ACCESS read-write
    STATUS current
    DESCRIPTION
        "action schedule end time (HH:MM)"
    ::= { actionSched 3 }
    --1.3.6.1.4.1.3052.17.2.14.3.3

actionSchedWeekdaysOnly OBJECT-TYPE
    SYNTAX DisplayString
    MAX-ACCESS read-write
    STATUS current
    DESCRIPTION
        "ON/OFF whether the action schedule applies to weekdays only
        (ON) or all days (OFF)"
    ::= { actionSched 4 }
    --1.3.6.1.4.1.3052.17.2.14.3.4

actionAsentriaRequireAck OBJECT-TYPE
    SYNTAX DisplayString
    MAX-ACCESS read-write
    STATUS current
    DESCRIPTION
        "ON/OFF Asentria action requires an ack from the receiver"
    ::= { actionAsentria 1 }
    --1.3.6.1.4.1.3052.17.2.14.4.1

actionAsentriaVersion OBJECT-TYPE
    SYNTAX DisplayString
    MAX-ACCESS read-write
    STATUS current
    DESCRIPTION
        "version 1.0 or 1.1"
    ::= { actionAsentria 2 }
    --1.3.6.1.4.1.3052.17.2.14.4.2

actionAsentriaTCPPort OBJECT-TYPE
    SYNTAX Integer32
    MAX-ACCESS read-write
    STATUS current
    DESCRIPTION
        "TCP port used for TCP-based Asentria alarms"
    ::= { actionAsentria 3 }
    --1.3.6.1.4.1.3052.17.2.14.4.3

actionHostTable OBJECT-TYPE
    SYNTAX SEQUENCE OF ActionHostConfig
    MAX-ACCESS not-accessible
    STATUS current
    DESCRIPTION
        "Table of network hosts to use for network-based actions"
    ::= { action 6 }
    --1.3.6.1.4.1.3052.17.2.14.6

actionHostEntry OBJECT-TYPE
    SYNTAX ActionHostConfig
    MAX-ACCESS not-accessible
    STATUS current
    DESCRIPTION
        "Entry for table of network hosts to use for network-based
        actions"
    INDEX { actionHostIndex }
    ::= { actionHostTable 1 }
    --1.3.6.1.4.1.3052.17.2.14.6.1

actionHostIndex OBJECT-TYPE
    SYNTAX Integer32 (1..6)
    MAX-ACCESS read-only
    STATUS current
    DESCRIPTION
        "Index for table of network hosts to use for network-based
        actions"
    ::= { actionHostEntry 1 }
    --1.3.6.1.4.1.3052.17.2.14.6.1.1

actionHost OBJECT-TYPE
    SYNTAX DisplayString
    MAX-ACCESS read-write
    STATUS current
    DESCRIPTION
        "Hostname/IP address used as destination for network-based
        action (e.g., trap)"
    ::= { actionHostEntry 2 }
    --1.3.6.1.4.1.3052.17.2.14.6.1.2

actionEmailTable OBJECT-TYPE
    SYNTAX SEQUENCE OF ActionEmailConfig
    MAX-ACCESS not-accessible
    STATUS current
    DESCRIPTION
        "Table of email addresses to use for email actions"
    ::= { action 7 }
    --1.3.6.1.4.1.3052.17.2.14.7

actionEmailEntry OBJECT-TYPE
    SYNTAX ActionEmailConfig
    MAX-ACCESS not-accessible
    STATUS current
    DESCRIPTION
        "Entry for table of email addresses to use for email actions"
    INDEX { actionEmailIndex }
    ::= { actionEmailTable 1 }
    --1.3.6.1.4.1.3052.17.2.14.7.1

actionEmailIndex OBJECT-TYPE
    SYNTAX Integer32 (1..6)
    MAX-ACCESS read-only
    STATUS current
    DESCRIPTION
        "Index for table of email addresses to use for email actions"
    ::= { actionEmailEntry 1 }
    --1.3.6.1.4.1.3052.17.2.14.7.1.1

actionEmail OBJECT-TYPE
    SYNTAX DisplayString
    MAX-ACCESS read-write
    STATUS current
    DESCRIPTION
        "email address"
    ::= { actionEmailEntry 2 }
    --1.3.6.1.4.1.3052.17.2.14.7.1.2

actionParseError OBJECT-TYPE
    SYNTAX DisplayString
    MAX-ACCESS read-only
    STATUS current
    DESCRIPTION
        "When a user attempts to configure an invalid action setting/
        object, this object says why it was invalid."
    ::= { action 8 }
    --1.3.6.1.4.1.3052.17.2.14.8

--***************************************************************************************
--System Section   2.16
--***************************************************************************************


sysTimeAutoDST OBJECT-TYPE
    SYNTAX DisplayString
    MAX-ACCESS read-write
    STATUS current
    DESCRIPTION
        "ON/OFF automatically adjust for Daylight Savings Time"
    ::= { sysTime 1 }
    --1.3.6.1.4.1.3052.17.2.16.1.1

sysTimeGMTOffset OBJECT-TYPE
    SYNTAX Integer32
    MAX-ACCESS read-write
    STATUS current
    DESCRIPTION
        "Absolute value of offset (hours) from GMT of the timezone"
    ::= { sysTime 2 }
    --1.3.6.1.4.1.3052.17.2.16.1.2

sysTimeGMTDirection OBJECT-TYPE
    SYNTAX DisplayString
    MAX-ACCESS read-write
    STATUS current
    DESCRIPTION
        "Direction (AHEAD/BEHIND) of timezone relative to GMT"
    ::= { sysTime 3 }
    --1.3.6.1.4.1.3052.17.2.16.1.3


sysTimeNetEnable OBJECT-TYPE
    SYNTAX DisplayString
    MAX-ACCESS read-write
    STATUS current
    DESCRIPTION
        "Network time mode"
    ::= { sysTimeNet 1 }
    --1.3.6.1.4.1.3052.17.2.16.1.4.1

sysTimeNetHostTable OBJECT-TYPE
    SYNTAX SEQUENCE OF NetworkTimeHostConfig
    MAX-ACCESS not-accessible
    STATUS current
    DESCRIPTION
        "Table of hosts to use for network time services"
    ::= { sysTimeNet 2 }
    --1.3.6.1.4.1.3052.17.2.16.1.4.2

sysTimeNetHostEntry OBJECT-TYPE
    SYNTAX NetworkTimeHostConfig
    MAX-ACCESS not-accessible
    STATUS current
    DESCRIPTION
        "Entry for table of hosts to use for network time services"
    INDEX { sysTimeNetHostIndex }
    ::= { sysTimeNetHostTable 1 }
    --1.3.6.1.4.1.3052.17.2.16.1.4.2.1

sysTimeNetHostIndex OBJECT-TYPE
    SYNTAX Integer32 (1..6)
    MAX-ACCESS read-only
    STATUS current
    DESCRIPTION
        "Index for table of hosts to use for network time services"
    ::= { sysTimeNetHostEntry 1 }
    --1.3.6.1.4.1.3052.17.2.16.1.4.2.1.1

sysTimeNetHost OBJECT-TYPE
    SYNTAX DisplayString
    MAX-ACCESS read-write
    STATUS current
    DESCRIPTION
        "host to use for network time services"
    ::= { sysTimeNetHostEntry 2 }
    --1.3.6.1.4.1.3052.17.2.16.1.4.2.1.2

sysPTTimeout  OBJECT-TYPE
    SYNTAX Integer32
    MAX-ACCESS read-write
    STATUS current
    DESCRIPTION
        "Timeout (minutes) of inactivity after which a pass-through
        session is terminated (0 means it never terminates)"
    ::= { sysPT 1 }
    --1.3.6.1.4.1.3052.17.2.16.2.1

sysPTEndPause OBJECT-TYPE
    SYNTAX Integer32
    MAX-ACCESS read-write
    STATUS current
    DESCRIPTION
        "number of 16ths of a second between escape characters
        received on pass-through origin IO handle that are reuired
        for the escape characters to register as pass-through escape
        characters in the pass-through escape sequence.  Set to 0 to
        make the escape character register as part of the pass-
        through escape sequence without requiring a pause."
    ::= { sysPT 2 }
    --1.3.6.1.4.1.3052.17.2.16.2.2

sysMTU OBJECT-TYPE
    SYNTAX Integer32
    MAX-ACCESS read-write
    STATUS current
    DESCRIPTION
        "Maximum transfer unit for ethernet interfaces"
    ::= { sys 3 }
    --1.3.6.1.4.1.3052.17.2.16.3

sysAnswerString OBJECT-TYPE
    SYNTAX DisplayString
    MAX-ACCESS read-write
    STATUS current
    DESCRIPTION
        "String displayed upon login"
    ::= { sys 4 }
    --1.3.6.1.4.1.3052.17.2.16.4

sysEventFileID OBJECT-TYPE
    SYNTAX DisplayString
    MAX-ACCESS read-write
    STATUS current
    DESCRIPTION
        "ID string for events file"
    ::= { sys 6 }
    --1.3.6.1.4.1.3052.17.2.16.6

sysEscapeCharacter OBJECT-TYPE
    SYNTAX Integer32
    MAX-ACCESS read-write
    STATUS current
    DESCRIPTION
        "Decimal ASCII code of the system escape character"
    ::= { sys 7 }
    --1.3.6.1.4.1.3052.17.2.16.7

sysTimeStampTimeFormat OBJECT-TYPE
    SYNTAX DisplayString
    MAX-ACCESS read-write
    STATUS current
    DESCRIPTION
        "Format of time stamp: HH:MM,HH:MM:SS,BLANK"
    ::= { sysTimeStamp 1 }
    --1.3.6.1.4.1.3052.17.2.16.8.1

sysTimeStampDateFormat OBJECT-TYPE
    SYNTAX DisplayString
    MAX-ACCESS read-write
    STATUS current
    DESCRIPTION
        "Format of date stamp: MM/DD,MM/DD/YY,MM/DD/YYYY,BLANK"
    ::= { sysTimeStamp 2 }
    --1.3.6.1.4.1.3052.17.2.16.8.2

sysTimeStampSpaceAfter OBJECT-TYPE
    SYNTAX DisplayString
    MAX-ACCESS read-write
    STATUS current
    DESCRIPTION
        "ON/OFF Inlude a space after timestamp"
    ::= { sysTimeStamp 3 }
    --1.3.6.1.4.1.3052.17.2.16.8.3

sysLogMode OBJECT-TYPE
    SYNTAX DisplayString
    MAX-ACCESS read-write
    STATUS current
    DESCRIPTION
        "Syslog mode: disabled, emit UDP (REMOTE), save in a
        rotating file set (FILE), or emit on a listening socket
        (SERVER)"
    ::= { sysLog 1 }
    --1.3.6.1.4.1.3052.17.2.16.9.1

sysLoghost OBJECT-TYPE
    SYNTAX DisplayString
    MAX-ACCESS read-write
    STATUS current
    DESCRIPTION
        "Syslog host: destination machine when syslog mode is REMOTE"
    ::= { sysLog 2 }
    --1.3.6.1.4.1.3052.17.2.16.9.2

sysLogFilter OBJECT-TYPE
    SYNTAX DisplayString
    MAX-ACCESS read-write
    STATUS current
    DESCRIPTION
        "String describing what functions place data in the syslog"
    ::= { sysLog 3 }
    --1.3.6.1.4.1.3052.17.2.16.9.3

sysLogFileSize OBJECT-TYPE
    SYNTAX Integer32
    MAX-ACCESS read-write
    STATUS current
    DESCRIPTION
        "Size (in KB) of syslog files (when syslog mode is SERVER or
        FILE)"
    ::= { sysLog 4 }
    --1.3.6.1.4.1.3052.17.2.16.9.4

sysLogFileCount OBJECT-TYPE
    SYNTAX Integer32
    MAX-ACCESS read-write
    STATUS current
    DESCRIPTION
        "Number of files in syslog file set (when syslog mode is
        SERVER or FILE)"
    ::= { sysLog 5 }
    --1.3.6.1.4.1.3052.17.2.16.9.5

sysLogListenPort OBJECT-TYPE
    SYNTAX Integer32
    MAX-ACCESS read-write
    STATUS current
    DESCRIPTION
        "TCP port on which the unit listens for a connection on
        which syslog data is dumped (when syslog mode is SERVER)"
    ::= { sysLog 6 }
    --1.3.6.1.4.1.3052.17.2.16.9.6

sysCRDBCapacity OBJECT-TYPE
    SYNTAX Integer32
    MAX-ACCESS read-only
    STATUS current
    DESCRIPTION
        "Capacity of Call Record Database (in KB)"
    ::= { sysCRDB 1 }
    --1.3.6.1.4.1.3052.17.2.10.1

sysCRDBPercentFull OBJECT-TYPE
    SYNTAX Integer32
    MAX-ACCESS read-only
    STATUS current
    DESCRIPTION
        "Percent of the CRDB used"
    ::= { sysCRDB 2 }
    --1.3.6.1.4.1.3052.17.2.10.2


sysCRDBFileIDTable OBJECT-TYPE
    SYNTAX SEQUENCE OF CRDBFileIDConfig
    MAX-ACCESS not-accessible
    STATUS current
    DESCRIPTION
        "Table of CRDB file IDs"
    ::= { sysCRDB 3 }
    --1.3.6.1.4.1.3052.17.2.16.10.3

sysCRDBFileIDEntry OBJECT-TYPE
    SYNTAX CRDBFileIDConfig
    MAX-ACCESS not-accessible
    STATUS current
    DESCRIPTION
        "Entry for table of CRDB file IDs"
    INDEX { sysCRDBFileIDIndex }
    ::= { sysCRDBFileIDTable 1 }
    --1.3.6.1.4.1.3052.17.2.16.10.3.1

sysCRDBFileIDIndex OBJECT-TYPE
    SYNTAX Integer32 (1..16)
    MAX-ACCESS read-only
    STATUS current
    DESCRIPTION
        "Index for table of CRDB file IDs"
    ::= { sysCRDBFileIDEntry 1 }
    --1.3.6.1.4.1.3052.17.2.16.10.3.1.1

sysCRDBFileID OBJECT-TYPE
    SYNTAX DisplayString
    MAX-ACCESS read-write
    STATUS current
    DESCRIPTION
        "ID of CRDB file for this port-associated file x"
    ::= { sysCRDBFileIDEntry 2 }
    --1.3.6.1.4.1.3052.17.2.16.10.3.1.2

sysCRDBFileEnforceMinTable OBJECT-TYPE
    SYNTAX SEQUENCE OF CRDBFileEnforceMinConfig
    MAX-ACCESS not-accessible
    STATUS current
    DESCRIPTION
        "Table of CRDB file minimum size enforcement settings"
    ::= { sysCRDB 4 }
    --1.3.6.1.4.1.3052.17.2.16.10.4

sysCRDBFileEnforceMinEntry OBJECT-TYPE
    SYNTAX CRDBFileEnforceMinConfig
    MAX-ACCESS not-accessible
    STATUS current
    DESCRIPTION
        "Entry for table of CRDB file minimum size enforcement
        settings"
    INDEX { sysCRDBFileEnforceMinIndex }
    ::= { sysCRDBFileEnforceMinTable 1 }
    --1.3.6.1.4.1.3052.17.2.16.10.4.1

sysCRDBFileEnforceMinIndex OBJECT-TYPE
    SYNTAX Integer32 (1..24)
    MAX-ACCESS read-only
    STATUS current
    DESCRIPTION
        "Index for table of CRDB file minimum size enforcement
        settings"
    ::= { sysCRDBFileEnforceMinEntry 1 }
    --1.3.6.1.4.1.3052.17.2.16.10.4.1.1

sysCRDBFileEnforceMin OBJECT-TYPE
    SYNTAX DisplayString
    MAX-ACCESS read-write
    STATUS current
    DESCRIPTION
        "ON/OFF: enforce minimum size for this CRDB file x"
    ::= { sysCRDBFileEnforceMinEntry 2 }
    --1.3.6.1.4.1.3052.17.2.16.10.4.1.2

sysCharMask OBJECT-TYPE
    SYNTAX OCTET STRING
    MAX-ACCESS read-write
    STATUS current
    DESCRIPTION
        "Character mask used for ignoring certain characters on
        serial ports when assembling data records (when port mode is
        ASCII)"
    ::= { sys 11 }
    --1.3.6.1.4.1.3052.17.2.16.11

sysPrompt OBJECT-TYPE
    SYNTAX DisplayString
    MAX-ACCESS read-write
    STATUS current
    DESCRIPTION
        "Prompt to use in a commnand session"
    ::= { sys 12 }
    --1.3.6.1.4.1.3052.17.2.16.12

sysBootStatus OBJECT-TYPE
    SYNTAX DisplayString
    MAX-ACCESS read-only
    STATUS current
    DESCRIPTION
        "String describing the boot status of the unit (Booted OK/
        still booting"
    ::= { sys 13 }
    --1.3.6.1.4.1.3052.17.2.16.13

--***************************************************************************************
--Sys Location Section 2.16.14
--***************************************************************************************

sysLocLatitude OBJECT-TYPE
    SYNTAX DisplayString
    MAX-ACCESS read-write
    STATUS current
    DESCRIPTION
        "Latitude portion of geographic coordinates as string"
    ::= { sysLoc 1 }
    --1.3.6.1.4.1.3052.17.2.16.14.1

sysLocLongitude OBJECT-TYPE
    SYNTAX DisplayString
    MAX-ACCESS read-write
    STATUS current
    DESCRIPTION
        "Longitude portion of geographic coordinates as string"
    ::= { sysLoc 2 }
    --1.3.6.1.4.1.3052.17.2.16.14.2

sysLocXOffset OBJECT-TYPE
    SYNTAX DisplayString
    MAX-ACCESS read-write
    STATUS current
    DESCRIPTION
        "X-offset portion of geographic coordinates as string"
    ::= { sysLoc 3 }
    --1.3.6.1.4.1.3052.17.2.16.14.3

sysLocYOffset OBJECT-TYPE
    SYNTAX DisplayString
    MAX-ACCESS read-write
    STATUS current
    DESCRIPTION
        "Y offset portion of geographic coordinates as string"
    ::= { sysLoc 4 }
    --1.3.6.1.4.1.3052.17.2.16.14.4

sysLocAngle OBJECT-TYPE
    SYNTAX DisplayString
    MAX-ACCESS read-write
    STATUS current
    DESCRIPTION
        "Angle portion of geographic coordinates as string"
    ::= { sysLoc 5 }
    --1.3.6.1.4.1.3052.17.2.16.14.5

sysLocAltitude OBJECT-TYPE
    SYNTAX DisplayString
    MAX-ACCESS read-write
    STATUS current
    DESCRIPTION
        "Altitude as string"
    ::= { sysLoc 6 }
    --1.3.6.1.4.1.3052.17.2.16.14.6

--***************************************************************************************
--Sys File Transfer Section 2.16.17
--***************************************************************************************

sysFileTransferStatus OBJECT-TYPE
    SYNTAX DisplayString
    MAX-ACCESS read-write
    STATUS current
    DESCRIPTION
        "Start/cancel file transfer, or check transfer status.  To start, set this object
        to 'start'.  To cancel, set this object to 'cancel'.  To check status, get the
        object"
    ::= { sysFileTransfer 1 }
    --1.3.6.1.4.1.3052.17.2.16.17.1

sysFileTransferURL OBJECT-TYPE
    SYNTAX DisplayString
    MAX-ACCESS read-write
    STATUS current
    DESCRIPTION
        "URL (describing protocol, host, directory, and file) on which file transfer
        function operates."
    ::= { sysFileTransfer 2 }
    --1.3.6.1.4.1.3052.17.2.16.17.2

sysFileTransferUsername OBJECT-TYPE
    SYNTAX DisplayString
    MAX-ACCESS read-write
    STATUS current
    DESCRIPTION
        "Username for user account at the resource specified by sysFileTransferURL."
    ::= { sysFileTransfer 3 }
    --1.3.6.1.4.1.3052.17.2.16.17.3

sysFileTransferPassword OBJECT-TYPE
    SYNTAX DisplayString
    MAX-ACCESS read-write
    STATUS current
    DESCRIPTION
        "Password for user account at the resource specified by sysFileTransferURL."
    ::= { sysFileTransfer 4 }
    --1.3.6.1.4.1.3052.17.2.16.17.4

--***************************************************************************************
--Sys Update Section 2.16.18
--***************************************************************************************

sysUpdateStatus OBJECT-TYPE
    SYNTAX DisplayString
    MAX-ACCESS read-only
    STATUS current
    DESCRIPTION
        "Check time/result of last update attempt."
    ::= { sysUpdate 1 }
    --1.3.6.1.4.1.3052.17.2.16.18.1


--***************************************************************************************
--Audit Log Section   2.17
--***************************************************************************************

auditLogEnable OBJECT-TYPE
    SYNTAX DisplayString
    MAX-ACCESS read-write
    STATUS current
    DESCRIPTION
        "ON/OFF enable audit log"
    ::= { auditLog 1 }
    --1.3.6.1.4.1.3052.17.2.17.1

auditLogStoreResets OBJECT-TYPE
    SYNTAX DisplayString
    MAX-ACCESS read-write
    STATUS current
    DESCRIPTION
        "ON/OFF audit log stores when the unit resets"
    ::= { auditLog 2 }
    --1.3.6.1.4.1.3052.17.2.17.1

auditLogStoreCommands OBJECT-TYPE
    SYNTAX DisplayString
    MAX-ACCESS read-write
    STATUS current
    DESCRIPTION
        "ON/OFF audit log stores commands entered in a command
        session"
    ::= { auditLog 3 }
    --1.3.6.1.4.1.3052.17.2.17.1

auditLogStoreRelays OBJECT-TYPE
    SYNTAX DisplayString
    MAX-ACCESS read-write
    STATUS current
    DESCRIPTION
        "ON/OFF audit log stores relay activity"
    ::= { auditLog 4 }
    --1.3.6.1.4.1.3052.17.2.17.1

auditLogStoreAlarmActions OBJECT-TYPE
    SYNTAX DisplayString
    MAX-ACCESS read-write
    STATUS current
    DESCRIPTION
        "ON/OFF audit log stores action delivery activity"
    ::= { auditLog 5 }
    --1.3.6.1.4.1.3052.17.2.17.1

auditLogStorePwdFailures OBJECT-TYPE
    SYNTAX DisplayString
    MAX-ACCESS read-write
    STATUS current
    DESCRIPTION
        "ON/OFF audit log stores when user was denied login"
    ::= { auditLog 6 }
    --1.3.6.1.4.1.3052.17.2.17.1

auditLogStoreLogins OBJECT-TYPE
    SYNTAX DisplayString
    MAX-ACCESS read-write
    STATUS current
    DESCRIPTION
        "ON/OFF audit log stores when a user was allowed login"
    ::= { auditLog 7 }
    --1.3.6.1.4.1.3052.17.2.17.1

auditLogStoreSHSK OBJECT-TYPE
    SYNTAX DisplayString
    MAX-ACCESS read-write
    STATUS current
    DESCRIPTION
        "ON/OFF audit log stores serial handshaking status
        (regardless of serial handshaking event)"
    ::= { auditLog 8 }
    --1.3.6.1.4.1.3052.17.2.17.1

auditLogStorePassthrough OBJECT-TYPE
    SYNTAX DisplayString
    MAX-ACCESS read-write
    STATUS current
    DESCRIPTION
        "ON/OFF audit log stores pass-through activity"
    ::= { auditLog 9 }
    --1.3.6.1.4.1.3052.17.2.17.1

auditLogStoreInactivity OBJECT-TYPE
    SYNTAX DisplayString
    MAX-ACCESS read-write
    STATUS current
    DESCRIPTION
        "ON/OFF audit log stores when sessions expire due to
        inactivity"
    ::= { auditLog 10 }
    --1.3.6.1.4.1.3052.17.2.17.1

auditLogStorePolling OBJECT-TYPE
    SYNTAX DisplayString
    MAX-ACCESS read-write
    STATUS current
    DESCRIPTION
        "ON/OFF audit log stores CRDB polling activity"
    ::= { auditLog 11 }
    --1.3.6.1.4.1.3052.17.2.17.1

auditLogMaxSize OBJECT-TYPE
    SYNTAX Integer32
    MAX-ACCESS read-write
    STATUS current
    DESCRIPTION
        "Maximum size (in KB) of audit log"
    ::= { auditLog 12 }
    --1.3.6.1.4.1.3052.17.2.17.1

--***************************************************************************************
--Scripting Section   2.17
--***************************************************************************************

scrGlobalEnable OBJECT-TYPE
    SYNTAX DisplayString
    MAX-ACCESS read-write
    STATUS current
    DESCRIPTION
        "ON/OFF enable scripting"
    ::= { scripting 1 }
    --1.3.6.1.4.1.3052.17.2.18.1

scrDTRCtrlPortEnableTable OBJECT-TYPE
    SYNTAX SEQUENCE OF ScriptingDTRCtrlPortEnableConfig
    MAX-ACCESS not-accessible
    STATUS current
    DESCRIPTION
        "Table of DTR control port enables"
    ::= { scripting 2 }
    --1.3.6.1.4.1.3052.17.2.18.2

scrDTRCtrlPortEnableEntry OBJECT-TYPE
    SYNTAX ScriptingDTRCtrlPortEnableConfig
    MAX-ACCESS not-accessible
    STATUS current
    DESCRIPTION
        "Entry for table of DTR control port enables"
    INDEX { scrDTRCtrlPortEnableIndex }
    ::= { scrDTRCtrlPortEnableTable 1 }
    --1.3.6.1.4.1.3052.17.2.18.2.1

scrDTRCtrlPortEnableIndex OBJECT-TYPE
    SYNTAX Integer32 (1..16)
    MAX-ACCESS read-only
    STATUS current
    DESCRIPTION
        "Index for table of DTR control port enables"
    ::= { scrDTRCtrlPortEnableEntry 1 }
    --1.3.6.1.4.1.3052.17.2.18.2.1.1

scrDTRCtrlPortEnable OBJECT-TYPE
    SYNTAX DisplayString
    MAX-ACCESS read-write
    STATUS current
    DESCRIPTION
        "ON/OFF enable DTR control of scripting for this port"
    ::= { scrDTRCtrlPortEnableEntry 2 }
    --1.3.6.1.4.1.3052.17.2.18.2.1.2


scrTable OBJECT-TYPE
    SYNTAX SEQUENCE OF ScriptingConfig
    MAX-ACCESS not-accessible
    STATUS current
    DESCRIPTION
        "Table of scripts"
    ::= { scripting 3 }
    --1.3.6.1.4.1.3052.17.2.18.3

scrEntry OBJECT-TYPE
    SYNTAX ScriptingConfig
    MAX-ACCESS not-accessible
    STATUS current
    DESCRIPTION
        "Entry for table of scripts"
    INDEX { scrIndex }
    ::= { scrTable 1 }
    --1.3.6.1.4.1.3052.17.2.18.3.1

scrIndex OBJECT-TYPE
    SYNTAX Integer32 (1..20)
    MAX-ACCESS read-only
    STATUS current
    DESCRIPTION
        "Index for table of scripts"
    ::= { scrEntry 1 }
    --1.3.6.1.4.1.3052.17.2.18.3.1.1

scrEnable OBJECT-TYPE
    SYNTAX DisplayString
    MAX-ACCESS read-write
    STATUS current
    DESCRIPTION
        "ON/OFF enable this script"
    ::= { scrEntry 2 }
    --1.3.6.1.4.1.3052.17.2.18.3.1.2

scrName OBJECT-TYPE
    SYNTAX DisplayString
    MAX-ACCESS read-write
    STATUS current
    DESCRIPTION
        "Name of this script"
    ::= { scrEntry 3 }
    --1.3.6.1.4.1.3052.17.2.18.3.1.3

scrFilename OBJECT-TYPE
    SYNTAX DisplayString
    MAX-ACCESS read-write
    STATUS current
    DESCRIPTION
        "Filename for this script"
    ::= { scrEntry 4 }
    --1.3.6.1.4.1.3052.17.2.18.3.1.4

scrRunAlways OBJECT-TYPE
    SYNTAX DisplayString
    MAX-ACCESS read-write
    STATUS current
    DESCRIPTION
        "ON/OFF: this script always runs"
    ::= { scrEntry 5 }
    --1.3.6.1.4.1.3052.17.2.18.3.1.5

scrRunAtStartup OBJECT-TYPE
    SYNTAX DisplayString
    MAX-ACCESS read-write
    STATUS current
    DESCRIPTION
        "ON/OFF: this script runs at startup"
    ::= { scrEntry 6 }
    --1.3.6.1.4.1.3052.17.2.18.3.1.6

scrRunScheduled OBJECT-TYPE
    SYNTAX DisplayString
    MAX-ACCESS read-write
    STATUS current
    DESCRIPTION
        "ON/OFF: this script runs at a certain time of day"
    ::= { scrEntry 7 }
    --1.3.6.1.4.1.3052.17.2.18.3.1.7

scrScheduleTime OBJECT-TYPE
    SYNTAX DisplayString
    MAX-ACCESS read-write
    STATUS current
    DESCRIPTION
        "Time of day (HH:MM) this script is scheduled to run"
    ::= { scrEntry 8 }
    --1.3.6.1.4.1.3052.17.2.18.3.1.8

scrArguments OBJECT-TYPE
    SYNTAX DisplayString
    MAX-ACCESS read-write
    STATUS current
    DESCRIPTION
        "Arguments for this script"
    ::= { scrEntry 9 }
    --1.3.6.1.4.1.3052.17.2.18.3.1.9

scrRepeatInterval OBJECT-TYPE
    SYNTAX Integer32
    MAX-ACCESS read-write
    STATUS current
    DESCRIPTION
        "How often this script runs (minutes)"
    ::= { scrEntry 10 }
    --1.3.6.1.4.1.3052.17.2.18.3.1.10

scrVolatileStringTable OBJECT-TYPE
    SYNTAX SEQUENCE OF ScriptingVolatileString
    MAX-ACCESS not-accessible
    STATUS current
    DESCRIPTION
        "Table of volatile string settings for use in
         scripts."
    ::= { scripting 4 }
    --1.3.6.1.4.1.3052.17.2.18.4

scrVolatileStringEntry OBJECT-TYPE
    SYNTAX ScriptingVolatileString
    MAX-ACCESS not-accessible
    STATUS current
    DESCRIPTION
        "Entry for table of volatile script string
        settings"
    INDEX { scrVolatileStringIndex }
    ::= { scrVolatileStringTable 1 }
    --1.3.6.1.4.1.3052.17.2.18.4.1

scrVolatileStringIndex OBJECT-TYPE
    SYNTAX Integer32 (1..50)
    MAX-ACCESS read-only
    STATUS current
    DESCRIPTION
        "Index for table of volatile script string
        settings"
    ::= { scrVolatileStringEntry 1 }
    --1.3.6.1.4.1.3052.17.2.18.4.1.1

scrVolatileString OBJECT-TYPE
    SYNTAX DisplayString
    MAX-ACCESS read-write
    STATUS current
    DESCRIPTION
        "Volatile string for use in scripts. Use this
         object to cache frequently-changing string values
         or string values that do not need to persist
         through reset.  This object corresponds to the
         scripting.vstring[] setting key branch; use those
         keys in scripts and you can view or change their
         values with this object."
    ::= { scrVolatileStringEntry 2 }
    --1.3.6.1.4.1.3052.17.2.18.4.1.2

scrVolatileIntTable OBJECT-TYPE
    SYNTAX SEQUENCE OF ScriptingVolatileInt
    MAX-ACCESS not-accessible
    STATUS current
    DESCRIPTION
        "Table of volatile integer settings for use in
         scripts."
    ::= { scripting 5 }
    --1.3.6.1.4.1.3052.17.2.18.5

scrVolatileIntEntry OBJECT-TYPE
    SYNTAX ScriptingVolatileInt
    MAX-ACCESS not-accessible
    STATUS current
    DESCRIPTION
        "Entry for table of volatile script integer
        settings"
    INDEX { scrVolatileIntIndex }
    ::= { scrVolatileIntTable 1 }
    --1.3.6.1.4.1.3052.17.2.18.5.1

scrVolatileIntIndex OBJECT-TYPE
    SYNTAX Integer32 (1..50)
    MAX-ACCESS read-only
    STATUS current
    DESCRIPTION
        "Index for table of volatile script integer
        settings"
    ::= { scrVolatileIntEntry 1 }
    --1.3.6.1.4.1.3052.17.2.18.5.1.1

scrVolatileInt OBJECT-TYPE
    SYNTAX Integer32 (0..2147483647)
    MAX-ACCESS read-write
    STATUS current
    DESCRIPTION
        "Volatile integer for use in scripts. Use this
         object to cache frequently-changing integer values
         or integer values that do not need to persist
         through reset.  This object corresponds to the
         scripting.vint[] setting key branch; use those
         keys in scripts and you can view or change their
         values with this object."
    ::= { scrVolatileIntEntry 2 }
    --1.3.6.1.4.1.3052.17.2.18.5.1.2

scrNonVolatileStringTable OBJECT-TYPE
    SYNTAX SEQUENCE OF ScriptingNonVolatileString
    MAX-ACCESS not-accessible
    STATUS current
    DESCRIPTION
        "Table of non-volatile string settings for use in
         scripts."
    ::= { scripting 6 }
    --1.3.6.1.4.1.3052.17.2.18.6

scrNonVolatileStringEntry OBJECT-TYPE
    SYNTAX ScriptingNonVolatileString
    MAX-ACCESS not-accessible
    STATUS current
    DESCRIPTION
        "Entry for table of non-volatile script string
        settings"
    INDEX { scrNonVolatileStringIndex }
    ::= { scrNonVolatileStringTable 1 }
    --1.3.6.1.4.1.3052.17.2.18.6.1

scrNonVolatileStringIndex OBJECT-TYPE
    SYNTAX Integer32 (1..50)
    MAX-ACCESS read-only
    STATUS current
    DESCRIPTION
        "Index for table of non-volatile script string
        settings"
    ::= { scrNonVolatileStringEntry 1 }
    --1.3.6.1.4.1.3052.17.2.18.6.1.1

scrNonVolatileString OBJECT-TYPE
    SYNTAX DisplayString
    MAX-ACCESS read-write
    STATUS current
    DESCRIPTION
        "Non-volatile string for use in scripts. Use this
         object to store values that need to persist
         through reset.  This object corresponds to the
         scripting.nvstring[] setting key branch; use those
         keys in scripts and you can view or change their
         values with this object.  Note: to store frequently-
         changing integers, use the scrVolatileString object,
         otherwise your scripts may cause unnecessary wear of
         the non-volatile storage medium on the unit."
    ::= { scrNonVolatileStringEntry 2 }
    --1.3.6.1.4.1.3052.17.2.18.6.1.2

scrNonVolatileIntTable OBJECT-TYPE
    SYNTAX SEQUENCE OF ScriptingNonVolatileInt
    MAX-ACCESS not-accessible
    STATUS current
    DESCRIPTION
        "Table of non-volatile integer settings for use in
         scripts."
    ::= { scripting 7 }
    --1.3.6.1.4.1.3052.17.2.18.7

scrNonVolatileIntEntry OBJECT-TYPE
    SYNTAX ScriptingNonVolatileInt
    MAX-ACCESS not-accessible
    STATUS current
    DESCRIPTION
        "Entry for table of non-volatile script integer
        settings"
    INDEX { scrNonVolatileIntIndex }
    ::= { scrNonVolatileIntTable 1 }
    --1.3.6.1.4.1.3052.17.2.18.7.1

scrNonVolatileIntIndex OBJECT-TYPE
    SYNTAX Integer32 (1..50)
    MAX-ACCESS read-only
    STATUS current
    DESCRIPTION
        "Index for table of non-volatile script integer
        settings"
    ::= { scrNonVolatileIntEntry 1 }
    --1.3.6.1.4.1.3052.17.2.18.7.1.1

scrNonVolatileInt OBJECT-TYPE
    SYNTAX Integer32 (0..2147483647)
    MAX-ACCESS read-write
    STATUS current
    DESCRIPTION
        "Non-volatile integer for use in scripts. Use this
         object to store integer values that need to persist
         through reset.  This object corresponds to the
         scripting.nvint[] setting key branch; use those
         keys in scripts and you can view or change their
         values with this object.  Note: to store frequently-
         changing integers, use the scrVolatileInt object,
         otherwise your scripts may cause unnecessary wear of
         the non-volatile storage medium on the unit."
    ::= { scrNonVolatileIntEntry 2 }
    --1.3.6.1.4.1.3052.17.2.18.7.1.2


--***************************************************************************************
--Generator Section   2.19
--***************************************************************************************

genSetEnable OBJECT-TYPE
    SYNTAX DisplayString
    MAX-ACCESS read-write
    STATUS current
    DESCRIPTION
        "Enable genset functionality; that is, a generator is in use."
    ::= { genSet 1 }
    --1.3.6.1.4.1.3052.17.2.19.1.1

genSetRelayEs OBJECT-TYPE
    SYNTAX Integer32 (1..200)
    MAX-ACCESS read-write
    STATUS current
    DESCRIPTION
        "Which EventSensor has the relay which starts the generator."
    ::= { genSetRelay 1 }
    --1.3.6.1.4.1.3052.17.2.19.1.2.1

genSetRelayPoint OBJECT-TYPE
    SYNTAX Integer32 (1..13)
    MAX-ACCESS read-write
    STATUS current
    DESCRIPTION
        "Which relay starts the generator."
    ::= { genSetRelay 2 }
    --1.3.6.1.4.1.3052.17.2.19.1.2.2

genSetRelayRunningstate OBJECT-TYPE
    SYNTAX DisplayString
    MAX-ACCESS read-write
    STATUS current
    DESCRIPTION
        "Which relay state corresponds with the generator starting/running."
    ::= { genSetRelay 3 }
    --1.3.6.1.4.1.3052.17.2.19.1.2.3

genSetCCEnable OBJECT-TYPE
    SYNTAX DisplayString
    MAX-ACCESS read-write
    STATUS current
    DESCRIPTION
        "Enable generator running detection functionality; that is, the
        associated CC is valid for determining if generator is running."
    ::= { genSetCC 1 }
    --1.3.6.1.4.1.3052.17.2.19.1.3.1

genSetCCEs OBJECT-TYPE
    SYNTAX Integer32 (1..200)
    MAX-ACCESS read-write
    STATUS current
    DESCRIPTION
        "Which CC EventSensor has the CC which is connected to the genertor
        running detection monitor."
    ::= { genSetCC 2 }
    --1.3.6.1.4.1.3052.17.2.19.1.3.2

genSetCCPoint OBJECT-TYPE
    SYNTAX Integer32 (1..64)
    MAX-ACCESS read-write
    STATUS current
    DESCRIPTION
        "Which CC is connected to the genertor running detection monitor."
    ::= { genSetCC 3 }
    --1.3.6.1.4.1.3052.17.2.19.1.3.3

genSetCCRunningState OBJECT-TYPE
    SYNTAX DisplayString
    MAX-ACCESS read-write
    STATUS current
    DESCRIPTION
        "Which CC physical state corresponds with the generator running."
    ::= { genSetCC 4 }
    --1.3.6.1.4.1.3052.17.2.19.1.3.4




genRunMode OBJECT-TYPE
    SYNTAX DisplayString
    MAX-ACCESS read-write
    STATUS current
    DESCRIPTION
        "Generator Exercising function main operating mode; set to INHIBIT
        to inhibit exercising the generator."
    ::= { genRun 1 }
    --1.3.6.1.4.1.3052.17.2.19.2.1

genRunSched OBJECT-TYPE
    SYNTAX DisplayString
    MAX-ACCESS read-write
    STATUS current
    DESCRIPTION
        "Schedule number(s) which govern(s) when Generator Exercising function
        runs."
    ::= { genRun 2 }
    --1.3.6.1.4.1.3052.17.2.19.2.2

genRunDuration OBJECT-TYPE
    SYNTAX Integer32 (600..3600)
    MAX-ACCESS read-write
    STATUS current
    DESCRIPTION
        "Number of seconds that generator should run, started when the
        generator needs to start by SCHEDULE or by being forced to start."
    ::= { genRun 3 }
    --1.3.6.1.4.1.3052.17.2.19.2.3

genRunForce OBJECT-TYPE
    SYNTAX Integer32 (0..1)
    MAX-ACCESS read-write
    STATUS current
    DESCRIPTION
        "Write 1 to this to force the generator exercising to start.  Always
        reads as 0."
    ::= { genRun 4 }
    --1.3.6.1.4.1.3052.17.2.19.2.4

genRunReqasm OBJECT-TYPE
    SYNTAX DisplayString
    MAX-ACCESS read-write
    STATUS current
    DESCRIPTION
        "Require ASM connectivity before starting the generator from a schedule."
    ::= { genRun 5 }
    --1.3.6.1.4.1.3052.17.2.19.2.5

genRunStatus OBJECT-TYPE
    SYNTAX DisplayString
    MAX-ACCESS read-only
    STATUS current
    DESCRIPTION
        "Status of Generator Exercising function."
    ::= { genRun 6 }
    --1.3.6.1.4.1.3052.17.2.19.2.6


genRunNonstartEventEnable OBJECT-TYPE
    SYNTAX DisplayString
    MAX-ACCESS read-write
    STATUS current
    DESCRIPTION
        "Enable generator non-start event."
    ::= { genRunNonstartEvent 1 }
    --1.3.6.1.4.1.3052.17.2.19.2.7.1

genRunNonstartEventActions OBJECT-TYPE
    SYNTAX DisplayString
    MAX-ACCESS read-write
    STATUS current
    DESCRIPTION
        "Actions for generator non-start event."
    ::= { genRunNonstartEvent 2 }
    --1.3.6.1.4.1.3052.17.2.19.2.7.2

genRunNonstartEventTrap OBJECT-TYPE
    SYNTAX Integer32 (536..1199)
    MAX-ACCESS read-write
    STATUS current
    DESCRIPTION
        "Trap number for generator non-start event."
    ::= { genRunNonstartEvent 3 }
    --1.3.6.1.4.1.3052.17.2.19.2.7.3

genRunNonstartEventClass OBJECT-TYPE
    SYNTAX DisplayString
    MAX-ACCESS read-write
    STATUS current
    DESCRIPTION
        "Class (severity) for generator non-start event."
    ::= { genRunNonstartEvent 4 }
    --1.3.6.1.4.1.3052.17.2.19.2.7.4


--***************************************************************************************
--Calendar Section   2.20
--***************************************************************************************

schedTable OBJECT-TYPE
    SYNTAX SEQUENCE OF ScheduleConfig
    MAX-ACCESS not-accessible
    STATUS current
    DESCRIPTION
        "Table of schedules"
    ::= { calendar 1 }
    --1.3.6.1.4.1.3052.17.2.20.1

schedEntry OBJECT-TYPE
    SYNTAX ScheduleConfig
    MAX-ACCESS not-accessible
    STATUS current
    DESCRIPTION
        "Entry for table of schedules."
    INDEX { schedIndex }
    ::= { schedTable 1 }
    --1.3.6.1.4.1.3052.17.2.20.1.1

schedIndex OBJECT-TYPE
    SYNTAX Integer32 (1..8)
    MAX-ACCESS read-only
    STATUS current
    DESCRIPTION
        "Index for table of schedules."
    ::= { schedEntry 1 }
    --1.3.6.1.4.1.3052.17.2.20.1.1.1

schedEnable OBJECT-TYPE
    SYNTAX DisplayString
    MAX-ACCESS read-write
    STATUS current
    DESCRIPTION
        "Enable this schedule."
    ::= { schedEntry 2 }
    --1.3.6.1.4.1.3052.17.2.20.1.1.2

schedStart OBJECT-TYPE
    SYNTAX DisplayString
    MAX-ACCESS read-write
    STATUS current
    DESCRIPTION
        "This is of the form 'mm/dd/yy hh:mm:ss'. This controls on which
        date/time the schedule starts."
    ::= { schedEntry 3 }
    --1.3.6.1.4.1.3052.17.2.20.1.1.3

schedRepeatMode OBJECT-TYPE
    SYNTAX DisplayString
    MAX-ACCESS read-write
    STATUS current
    DESCRIPTION
        "Controls in which way the schedule should repeat."
    ::= { schedEntry 4 }
    --1.3.6.1.4.1.3052.17.2.20.1.1.4

schedRepeatFreq OBJECT-TYPE
    SYNTAX Integer32 (1..400)
    MAX-ACCESS read-write
    STATUS current
    DESCRIPTION
        "Controls how often the schedule should repeat: every nth day, week,
        month, or year."
    ::= { schedEntry 5 }
    --1.3.6.1.4.1.3052.17.2.20.1.1.5

schedRepeatEndMode OBJECT-TYPE
    SYNTAX DisplayString
    MAX-ACCESS read-write
    STATUS current
    DESCRIPTION
        "Controls how the repeating schedule should end."
    ::= { schedEntry 6 }
    --1.3.6.1.4.1.3052.17.2.20.1.1.6

schedRepeatEndAfter OBJECT-TYPE
    SYNTAX Integer32 (1..1000)
    MAX-ACCESS read-write
    STATUS current
    DESCRIPTION
        "Number of times this schedule should be repeated; relevant when the
        repeat end mode is AFTER."
    ::= { schedEntry 7 }
    --1.3.6.1.4.1.3052.17.2.20.1.1.7

schedRepeatEndOn OBJECT-TYPE
    SYNTAX DisplayString
    MAX-ACCESS read-write
    STATUS current
    DESCRIPTION
        "Date/time (in the form 'mm/yy/dd hh:mm:ss' or blank string) after
        which repeating should end, relevant when repeat end mode is ON DATE."
    ::= { schedEntry 8 }
    --1.3.6.1.4.1.3052.17.2.20.1.1.8

schedRepeatWeeklySun OBJECT-TYPE
    SYNTAX DisplayString
    MAX-ACCESS read-write
    STATUS current
    DESCRIPTION
        "Run this schedule on Sunday(s); relevant when repeat mode is weekly."
    ::= { schedEntry 9 }
    --1.3.6.1.4.1.3052.17.2.20.1.1.9

schedRepeatWeeklyMon OBJECT-TYPE
    SYNTAX DisplayString
    MAX-ACCESS read-write
    STATUS current
    DESCRIPTION
        "Run this schedule on Monday(s); relevant when repeat mode is weekly."
    ::= { schedEntry 10 }
    --1.3.6.1.4.1.3052.17.2.20.1.1.10

schedRepeatWeeklyTue OBJECT-TYPE
    SYNTAX DisplayString
    MAX-ACCESS read-write
    STATUS current
    DESCRIPTION
        "Run this schedule on Tuesday(s); relevant when repeat mode is weekly."
    ::= { schedEntry 11 }
    --1.3.6.1.4.1.3052.17.2.20.1.1.11

schedRepeatWeeklyWed OBJECT-TYPE
    SYNTAX DisplayString
    MAX-ACCESS read-write
    STATUS current
    DESCRIPTION
        "Run this schedule on Wednesday(s); relevant when repeat mode is weekly."
    ::= { schedEntry 12 }
    --1.3.6.1.4.1.3052.17.2.20.1.1.12

schedRepeatWeeklyThu OBJECT-TYPE
    SYNTAX DisplayString
    MAX-ACCESS read-write
    STATUS current
    DESCRIPTION
        "Run this schedule on Thursday(s); relevant when repeat mode is weekly."
    ::= { schedEntry 13 }
    --1.3.6.1.4.1.3052.17.2.20.1.1.13

schedRepeatWeeklyFri OBJECT-TYPE
    SYNTAX DisplayString
    MAX-ACCESS read-write
    STATUS current
    DESCRIPTION
        "Run this schedule on Friday(s); relevant when repeat mode is weekly."
    ::= { schedEntry 14 }
    --1.3.6.1.4.1.3052.17.2.20.1.1.14

schedRepeatWeeklySat OBJECT-TYPE
    SYNTAX DisplayString
    MAX-ACCESS read-write
    STATUS current
    DESCRIPTION
        "Run this schedule on Saturday(s); relevant when repeat mode is weekly."
    ::= { schedEntry 15 }
    --1.3.6.1.4.1.3052.17.2.20.1.1.15

schedRepeatMonthlyMode OBJECT-TYPE
    SYNTAX DisplayString
    MAX-ACCESS read-write
    STATUS current
    DESCRIPTION
        "EACH means the schedule runs on specific dates of the month. ON THE
        means the schedule runs on calculated dates of the month according to
        which day that month starts."
    ::= { schedEntry 16 }
    --1.3.6.1.4.1.3052.17.2.20.1.1.16

schedRepeatMonthlyDates OBJECT-TYPE
    SYNTAX DisplayString
    MAX-ACCESS read-write
    STATUS current
    DESCRIPTION
        "Comma-separated list of dates of a month on which this schedule should
        run, relevant when repeat monthly mode is EACH."
    ::= { schedEntry 17 }
    --1.3.6.1.4.1.3052.17.2.20.1.1.17

schedRepeatMonthlyOnThe OBJECT-TYPE
    SYNTAX DisplayString
    MAX-ACCESS read-write
    STATUS current
    DESCRIPTION
        "Controls on which day of the month this schedule should run, relevant
        when repeat monthly mode is ON THE."
    ::= { schedEntry 18 }
    --1.3.6.1.4.1.3052.17.2.20.1.1.18

schedRepeatMonthlyOnDay OBJECT-TYPE
    SYNTAX DisplayString
    MAX-ACCESS read-write
    STATUS current
    DESCRIPTION
        "Controls the day of week on which this schedule is run, relevant when
        repeat monthly mode is ON THE"
    ::= { schedEntry 19 }
    --1.3.6.1.4.1.3052.17.2.20.1.1.19

schedRepeatYearlyJan OBJECT-TYPE
    SYNTAX DisplayString
    MAX-ACCESS read-write
    STATUS current
    DESCRIPTION
        "Run this schedule in January, relevant when repeat mode is YEARLY."
    ::= { schedEntry 20 }
    --1.3.6.1.4.1.3052.17.2.20.1.1.20

schedRepeatYearlyFeb OBJECT-TYPE
    SYNTAX DisplayString
    MAX-ACCESS read-write
    STATUS current
    DESCRIPTION
        "Run this schedule in February, relevant when repeat mode is YEARLY."
    ::= { schedEntry 21 }
    --1.3.6.1.4.1.3052.17.2.20.1.1.21

schedRepeatYearlyMar OBJECT-TYPE
    SYNTAX DisplayString
    MAX-ACCESS read-write
    STATUS current
    DESCRIPTION
        "Run this schedule in March, relevant when repeat mode is YEARLY."
    ::= { schedEntry 22 }
    --1.3.6.1.4.1.3052.17.2.20.1.1.22

schedRepeatYearlyApr OBJECT-TYPE
    SYNTAX DisplayString
    MAX-ACCESS read-write
    STATUS current
    DESCRIPTION
        "Run this schedule in April, relevant when repeat mode is YEARLY."
    ::= { schedEntry 23 }
    --1.3.6.1.4.1.3052.17.2.20.1.1.23

schedRepeatYearlyMay OBJECT-TYPE
    SYNTAX DisplayString
    MAX-ACCESS read-write
    STATUS current
    DESCRIPTION
        "Run this schedule in May, relevant when repeat mode is YEARLY."
    ::= { schedEntry 24 }
    --1.3.6.1.4.1.3052.17.2.20.1.1.24

schedRepeatYearlyJun OBJECT-TYPE
    SYNTAX DisplayString
    MAX-ACCESS read-write
    STATUS current
    DESCRIPTION
        "Run this schedule in June, relevant when repeat mode is YEARLY."
    ::= { schedEntry 25 }
    --1.3.6.1.4.1.3052.17.2.20.1.1.25

schedRepeatYearlyJul OBJECT-TYPE
    SYNTAX DisplayString
    MAX-ACCESS read-write
    STATUS current
    DESCRIPTION
        "Run this schedule in July, relevant when repeat mode is YEARLY."
    ::= { schedEntry 26 }
    --1.3.6.1.4.1.3052.17.2.20.1.1.26

schedRepeatYearlyAug OBJECT-TYPE
    SYNTAX DisplayString
    MAX-ACCESS read-write
    STATUS current
    DESCRIPTION
        "Run this schedule in August, relevant when repeat mode is YEARLY."
    ::= { schedEntry 27 }
    --1.3.6.1.4.1.3052.17.2.20.1.1.27

schedRepeatYearlySep OBJECT-TYPE
    SYNTAX DisplayString
    MAX-ACCESS read-write
    STATUS current
    DESCRIPTION
        "Run this schedule in September, relevant when repeat mode is YEARLY."
    ::= { schedEntry 28 }
    --1.3.6.1.4.1.3052.17.2.20.1.1.28

schedRepeatYearlyOct OBJECT-TYPE
    SYNTAX DisplayString
    MAX-ACCESS read-write
    STATUS current
    DESCRIPTION
        "Run this schedule in October, relevant when repeat mode is YEARLY."
    ::= { schedEntry 29 }
    --1.3.6.1.4.1.3052.17.2.20.1.1.29

schedRepeatYearlyNov OBJECT-TYPE
    SYNTAX DisplayString
    MAX-ACCESS read-write
    STATUS current
    DESCRIPTION
        "Run this schedule in November, relevant when repeat mode is YEARLY."
    ::= { schedEntry 30 }
    --1.3.6.1.4.1.3052.17.2.20.1.1.30

schedRepeatYearlyDec OBJECT-TYPE
    SYNTAX DisplayString
    MAX-ACCESS read-write
    STATUS current
    DESCRIPTION
        "Run this schedule in December, relevant when repeat mode is YEARLY."
    ::= { schedEntry 31 }
    --1.3.6.1.4.1.3052.17.2.20.1.1.31

schedRepeatYearlyOnThe OBJECT-TYPE
    SYNTAX DisplayString
    MAX-ACCESS read-write
    STATUS current
    DESCRIPTION
        "Controls on which day of the month this schedule should run, relevant
        when repeat mode is YEARLY."
    ::= { schedEntry 32 }
    --1.3.6.1.4.1.3052.17.2.20.1.1.32

schedRepeatYearlyOnDay OBJECT-TYPE
    SYNTAX DisplayString
    MAX-ACCESS read-write
    STATUS current
    DESCRIPTION
        "Controls the day of week on which this schedule is run, relevant when
        repeat mode is YEARLY."
    ::= { schedEntry 33 }
    --1.3.6.1.4.1.3052.17.2.20.1.1.33

schedNextTrigger OBJECT-TYPE
    SYNTAX DisplayString
    MAX-ACCESS read-only
    STATUS current
    DESCRIPTION
        "When this schedule will next trigger."
    ::= { schedEntry 34 }
    --1.3.6.1.4.1.3052.17.2.20.1.1.34


--***************************************************************************************
--Product IDs Section   3
--***************************************************************************************

siteName OBJECT-TYPE
    SYNTAX DisplayString
    MAX-ACCESS read-only
    STATUS current
    DESCRIPTION
        "Site Name string; Max 40 characters."
    ::= { productIds 1 }
    --1.3.6.1.4.1.3052.17.3.1

thisProduct OBJECT-TYPE
    SYNTAX DisplayString
    MAX-ACCESS read-only
    STATUS current
    DESCRIPTION
        "This is a factory configured string for the
        product name."
    ::= { productIds 2 }
    --1.3.6.1.4.1.3052.17.3.2

stockTrapString OBJECT-TYPE
    SYNTAX DisplayString
    MAX-ACCESS read-only
    STATUS current
    DESCRIPTION
        "The message defined for the event that triggers a trap."
    ::= { productIds 3 }
    --1.3.6.1.4.1.3052.17.3.3

trapEventTypeNumber OBJECT-TYPE
    SYNTAX Integer32
    MAX-ACCESS read-only
    STATUS current
    DESCRIPTION
        "The user-defined trap variable for the type of
        event that happened.  Here are the definitions:
           4    SCHEDULED
           7    Serial Handshaking Low
           8    Serial Handshaking High
           10   Contact Closure Active
           11   Contact Closure Inactive
           12   Temperature High
           13   Temperature Very High
           14   Temperature Low
           15   Temperature Very Low
           16   Temperature Return to Normal
           17   Humidity High
           18   Humidity Very High
           19   Humidity Low
           20   Humidity Very Low
           21   Humidity Return to Normal
           26   Analog High
           27   Analog Very High
           28   Analog Low
           29   Analog Very Low
           30   Analog Normal
           40   EventSensor Unresponsive
           100  Contact Closure Active Reminder
           101  Temperature High Reminder
           102  Temperature High Very Reminder
           103  Temperature Low Reminder
           104  Temperature Very Low Reminder
           105  Humidity High Reminder
           106  Humidity Very High Reminder
           107  Humidity Low Reminder
           108  Humidity Very Low Reminder
           109  Analog High Reminder
           110  Analog Very High Reminder
           111  Analog Low Reminder
           112  Analog Very Low Reminder"
    ::= { productIds 4 }
    --1.3.6.1.4.1.3052.17.3.4

trapEventTypeName OBJECT-TYPE
    SYNTAX DisplayString
    MAX-ACCESS read-only
    STATUS current
    DESCRIPTION
        "The user-defined trap variable for the string
        corresponding to the event type."
    ::= { productIds 5 }
    --1.3.6.1.4.1.3052.17.3.5

trapIncludedValue OBJECT-TYPE
    SYNTAX Integer32 (-2147483648..2147483647)
    MAX-ACCESS read-only
    STATUS current
    DESCRIPTION
        "The user-defined trap variable for the generic
        included value."
    ::= { productIds 6 }
    --1.3.6.1.4.1.3052.17.3.6

trapIncludedString OBJECT-TYPE
    SYNTAX DisplayString
    MAX-ACCESS read-only
    STATUS current
    DESCRIPTION
        "The user-defined trap variable for the generic
        included string."
    ::= { productIds 7 }
    --1.3.6.1.4.1.3052.17.3.7

trapTypeString OBJECT-TYPE
    SYNTAX DisplayString
    MAX-ACCESS read-only
    STATUS current
    DESCRIPTION
        "The cause of the trap, added for DL880 compatibility."
    ::= { productIds 8 }
    --1.3.6.1.4.1.3052.17.3.8

trapEventClassNumber OBJECT-TYPE
    SYNTAX Integer32
    MAX-ACCESS read-only
    STATUS current
    DESCRIPTION
        "The user-defined trap variable for the configurable
        class number associated with the triggering event."
    ::= { productIds 9 }
    --1.3.6.1.4.1.3052.17.3.9

trapEventClassName OBJECT-TYPE
    SYNTAX DisplayString
    MAX-ACCESS read-only
    STATUS current
    DESCRIPTION
        "The user-defined trap variable for the configurable
         class name associated with the class number."
    ::= { productIds 10 }
    --1.3.6.1.4.1.3052.17.3.10


--***************************************************************************************
--Key Interface Section 4
--***************************************************************************************

keyInterface OBJECT-TYPE
    SYNTAX DisplayString
    MAX-ACCESS read-write
    STATUS current
    DESCRIPTION
        "This object represents a setting key interface.  When
        setting this object, the value to set is the 'sk' command
        you would enter on the command line (without the 'sk').  To
        get the result of the operation, read this object after you
        write it.

        For example, to configure EventSensor 1 contact closure 34
        event actions to be an SNMP InformRequest to host foo, set
        this object to:
        'event.sensor[1].cc[34].eventactions=inform(foo)'.  The SNMP
        response is the result of the operation: if setting that key
        to that value was a success then the SNMP response will be a
        success and the response value will be what you had set.  If
        you subsequently read this object then you will see a
        message 'OK: ...'.

        If setting that key to that value failed then the SNMP
        response will be a failure (a badValue response).  If you
        subsequently read this object then the value returned is the
        reason that setting that key to that value failed.

        For another example, to read user 3's pass-through access
        for port 7, set this object to:
        'sec.user[3].port[7].ptaccess'.  The SNMP response is the
        result of the operation: if reading that key is a success
        then the SNMP response will be a success and the response
        value will be what you had SET (i.e., the opertion of
        reading a key, which is just the key itself with no '='
        operator, and this is not the key value you want to read).
        If you subsequently read this object then the value
        returned is the value of the key you want to read.

        If reading that key failed (e.g., if the key is invalid)
        then the SNMP response to your SNMP set operation (the
        value you set being the invalid key to read) will be a
        failure (a badValue response).  If you subsequently read
        this object then the value returned is the reason that
        reading that key failed (i.e., 'invalid key')."
    ::= { s450 4 }
    --1.3.6.1.4.1.3052.17.4


--***************************************************************************************
--TABLE DEFINITIONS
--***************************************************************************************

ESPointConfigTemp ::=
    SEQUENCE {
        espcTempIndexES
            Integer32,
        espcTempIndexPoint
            Integer32,
        espcTempEnable
            DisplayString,
        espcTempScale
            DisplayString,
        espcTempDeadband
            DisplayString,
        espcTempVHighTemp
            DisplayString,
        espcTempVHighActions
            DisplayString,
        espcTempVHighTrapnum
            Integer32,
        espcTempVHighClass
            DisplayString,
        espcTempHighTemp
            DisplayString,
        espcTempHighActions
            DisplayString,
        espcTempHighTrapnum
            Integer32,
        espcTempHighClass
            DisplayString,
        espcTempNormalActions
            DisplayString,
        espcTempNormalTrapnum
            Integer32,
        espcTempNormalClass
            DisplayString,
        espcTempLowTemp
            DisplayString,
        espcTempLowActions
            DisplayString,
        espcTempLowTrapnum
            Integer32,
        espcTempLowClass
            DisplayString,
        espcTempVLowTemp
            DisplayString,
        espcTempVLowActions
            DisplayString,
        espcTempVLowTrapnum
            Integer32,
        espcTempVLowClass
            DisplayString
}


ESPointConfigCC ::=
    SEQUENCE {
        espcCCIndexES
            Integer32,
        espcCCIndexPoint
            Integer32,
        espcCCEnable
            DisplayString,
        espcCCName
            DisplayString,
        espcCCEventState
            DisplayString,
        espcCCThreshold
            Integer32,
        espcCCEventActions
            DisplayString,
        espcCCEventTrapnum
            Integer32,
        espcCCEventClass
            DisplayString,
        espcCCNormalActions
            DisplayString,
        espcCCNormalTrapnum
            Integer32,
        espcCCNormalClass
            DisplayString,
        espcCCAlarmAlias
            DisplayString,
        espcCCNormalAlias
            DisplayString,
    espcCCNormalThreshold
            Integer32
}

ESPointConfigHumid ::=
    SEQUENCE {
        espcHumidIndexES
            Integer32,
        espcHumidIndexPoint
            Integer32,
        espcHumidEnable
            DisplayString,
        espcHumidDeadband
            Integer32,
        espcHumidVHighHumid
            Integer32,
        espcHumidVHighActions
            DisplayString,
        espcHumidVHighTrapnum
            Integer32,
        espcHumidVHighClass
            DisplayString,
        espcHumidHighHumid
            Integer32,
        espcHumidHighActions
            DisplayString,
        espcHumidHighTrapnum
            Integer32,
        espcHumidHighClass
            DisplayString,
        espcHumidNormalActions
            DisplayString,
        espcHumidNormalTrapnum
            Integer32,
        espcHumidNormalClass
            DisplayString,
        espcHumidLowHumid
            Integer32,
        espcHumidLowActions
            DisplayString,
        espcHumidLowTrapnum
            Integer32,
        espcHumidLowClass
            DisplayString,
        espcHumidVLowHumid
            Integer32,
        espcHumidVLowActions
            DisplayString,
        espcHumidVLowTrapnum
            Integer32,
        espcHumidVLowClass
            DisplayString
}

ESPointConfigAnalogInput ::=
    SEQUENCE {
    espcAIIndexES
            Integer32,
    espcAIIndexPoint
            Integer32,
    espcAIEnable
            DisplayString,
    espcAIPolarity
            DisplayString,
    espcAIDeadband
            Integer32,
    espcAIVhighValue
            Integer32,
    espcAIVhighActions
            DisplayString,
    espcAIVhighTrapnum
            Integer32,
    espcAIVhighClass
            DisplayString,
    espcAIHighValue
            Integer32,
    espcAIHighActions
            DisplayString,
    espcAIHighTrapnum
            Integer32,
    espcAIHighClass
            DisplayString,
    espcAINormalActions
            DisplayString,
    espcAINormalTrapnum
            Integer32,
    espcAINormalClass
            DisplayString,
    espcAILowValue
            Integer32,
    espcAILowActions
            DisplayString,
    espcAILowTrapnum
            Integer32,
    espcAILowClass
            DisplayString,
    espcAIVlowValue
            Integer32,
    espcAIVlowActions
            DisplayString,
    espcAIVlowTrapnum
            Integer32,
    espcAIVlowClass
            DisplayString,
    espcAIConvUnitName
            DisplayString,
    espcAIConvHighValue
            Integer32,
    espcAIConvHighUnit
            Integer32,
    espcAIConvHighSign
            DisplayString,
    espcAIConvLowValue
            Integer32,
    espcAIConvLowUnit
            Integer32,
    espcAIConvLowSign
            DisplayString
}

EventClassConfig ::=
    SEQUENCE {
        evClassNameIndex
            Integer32,
        evClassName
            DisplayString
}

RTSFileConfig ::=
    SEQUENCE {
        rtsFileIndex
            Integer32,
        rtsFileMode
            DisplayString,
        rtsFileShowAnswer
            DisplayString,
        rtsFileReqXON
            DisplayString,
        rtsFileTimeout
            Integer32,
        rtsFileEmptyClose
            DisplayString,
        rtsFilePushHost
            DisplayString,
        rtsFilePushPort
            Integer32,
        rtsFilePushRetryTimer
            Integer32
}


ScriptingConfig ::=
    SEQUENCE {
        scrIndex
            Integer32,
        scrEnable
            DisplayString,
        scrName
            DisplayString,
        scrFilename
            DisplayString,
        scrRunAlways
            DisplayString,
        scrRunAtStartup
            DisplayString,
        scrRunScheduled
            DisplayString,
        scrScheduleTime
            DisplayString,
        scrArguments
            DisplayString,
        scrRepeatInterval
            Integer32
}

ScriptingDTRCtrlPortEnableConfig ::=
    SEQUENCE {
        scrDTRCtrlPortEnableIndex
            Integer32,
        scrDTRCtrlPortEnable
            DisplayString

}

ScriptingVolatileString ::=
    SEQUENCE {
        scrVolatileStringIndex
            Integer32,
        scrVolatileString
            DisplayString
}

ScriptingVolatileInt ::=
    SEQUENCE {
        scrVolatileIntIndex
            Integer32,
        scrVolatileInt
            Integer32
}

ScriptingNonVolatileString ::=
    SEQUENCE {
        scrNonVolatileStringIndex
            Integer32,
        scrNonVolatileString
            DisplayString
}

ScriptingNonVolatileInt ::=
    SEQUENCE {
        scrNonVolatileIntIndex
            Integer32,
        scrNonVolatileInt
            Integer32
}

CRDBFileEnforceMinConfig ::=
    SEQUENCE {
        sysCRDBFileEnforceMinIndex
            Integer32,
        sysCRDBFileEnforceMin
            DisplayString
}

CRDBFileIDConfig ::=
    SEQUENCE {
        sysCRDBFileIDIndex
            Integer32,
        sysCRDBFileID
            DisplayString
}

NetworkTimeHostConfig ::=
    SEQUENCE {
        sysTimeNetHostIndex
            Integer32,
        sysTimeNetHost
            DisplayString
}

ActionHostConfig ::=
    SEQUENCE {
        actionHostIndex
            Integer32,
        actionHost
            DisplayString
}

ActionEmailConfig ::=
    SEQUENCE {
        actionEmailIndex
            Integer32,
        actionEmail
            DisplayString
}

FileEnforceMinimumConfig ::=
    SEQUENCE {
        sysCRDBFileEnforceMinIndex
            Integer32,
        sysCRDBFileEnforceMin
            DisplayString
}

SerialHandshakingLowEventConfig ::=
    SEQUENCE {
        evShskLowIndex
            Integer32,
        evShskLowEnable
            DisplayString,
        evShskLowActions
            DisplayString,
        evShskLowMessage
            DisplayString,
        evShskLowClass
            DisplayString,
        evShskLowTrapNum
            Integer32
}

SerialHandshakingHighEventConfig ::=
    SEQUENCE {
        evShskHighIndex
            Integer32,
        evShskHighEnable
            DisplayString,
        evShskHighActions
            DisplayString,
        evShskHighMessage
            DisplayString,
        evShskHighClass
            DisplayString,
        evShskHighTrapNum
            Integer32
}

SecUserConfig ::=
    SEQUENCE {
        secUserIndex
            Integer32,
        secUserEnable
            DisplayString,
        secUserConnectVia
            DisplayString,
        secUserLoginTo
            DisplayString,
        secUserAccessFile
            DisplayString,
        secUserPTEscapeTo
            DisplayString,
        secUserPPPType
            DisplayString,
        secUserRights
            DisplayString,
        secUserEventsReadAccess
            DisplayString,
        secUserAuditReadAccess
            DisplayString,
        secUserEventsWriteAccess
            DisplayString,
        secUserAuditWriteAccess
            DisplayString,
        secUserExpiration
            DisplayString,
        secUserCallbackNumber1
            DisplayString,
        secUserCallbackNumber2
            DisplayString,
        secUserCallbackNumber3
            DisplayString,
        secUserChallengeTelnetMode
            DisplayString,
        secUserChallengeModemMode
            DisplayString,
        secUserChallengeConsoleMode
            DisplayString,
        secUserChallengeTelnetSendTo
            DisplayString,
        secUserChallengeModemSendTo
            DisplayString,
        secUserChallengeExpiration
            Integer32
}



IPRestrictionConfig ::=
    SEQUENCE {
        ipRestrictionIndex
            Integer32,
        ipRestrictionEnable
            DisplayString,
        ipRestrictionMask
            IpAddress
}

DNSConfig ::=
    SEQUENCE {
        dnsIndex
            Integer32,
        dnsAddress
            IpAddress
}

HostConfig ::=
    SEQUENCE {
        hostIndex
            Integer32,
        hostDeclaration
            DisplayString
}

SNMPProxyTable ::=
    SEQUENCE {
        snmpProxyIndex
            Integer32,
        snmpProxyOIDBranch
            DisplayString,
        snmpProxyIP
            DisplayString,
        snmpProxyPort
            Integer32
}

SNMPPollRequestConfig ::=
    SEQUENCE {
        snmpPRequestIndex
            Integer32,
        snmpPRequestDescription
            DisplayString,
        snmpPRequestAgent
            DisplayString,
        snmpPRequestReadcom
            DisplayString,
        snmpPRequestOID
            DisplayString,
        snmpPRequestPeriod
            Integer32,
        snmpPRequestResultStatus
            DisplayString,
        snmpPRequestResultValue
            DisplayString,
        snmpPRequestResultTime
            DisplayString,
        snmpPRequestResultType
            DisplayString
}

FTPPushPushFileConfig ::=
    SEQUENCE {
        ftpPushPushFileIndex
            Integer32,
        ftpPushPushFile
            DisplayString
}

FTPPushRemoteFileConfig ::=
    SEQUENCE {
        ftpPushRemoteFileIndex
            Integer32,
        ftpPushRemoteFileName
            DisplayString
}

PortConfig ::=
    SEQUENCE {
        portConfigIndex
            Integer32,
        portConfigBaud
            Integer32,
        portConfigDataFormat
            Integer32,
        portConfigStripPtOutputLfs
            Integer32,
        portConfigStripPtInputLfs
            Integer32,
        portConfigMaskEnable
            Integer32,
        portConfigDAEnable
            Integer32,
        portConfigStoreAlarmsDPT
            DisplayString,
        portConfigRecordTimeout
            Integer32,
        portConfigDataType
            DisplayString,
        portConfigEtxToCRLF
            DisplayString,
        portConfigMLREnable
            DisplayString,
        portConfigMLRStartField1Pos
            Integer32,
        portConfigMLRStartField1Text
            DisplayString,
        portConfigMLRStartField2Pos
            Integer32,
        portConfigMLRStartField2Text
            DisplayString,
        portConfigMLRNumLinesBefore
            Integer32,
        portConfigMLREndDetection
            DisplayString,
        portConfigMLRLineCount
            Integer32,
        portConfigMLREndField1Pos
            Integer32,
        portConfigMLREndField1Text
            DisplayString,
        portConfigMLREndField2Pos
            Integer32,
        portConfigMLREndField2Text
            DisplayString,
        portConfigMLRUseComplexRules
            DisplayString,
        portConfigBufferPT
            DisplayString,
        portConfigId
            DisplayString

}

ESPoint ::=
    SEQUENCE {
        esIndexES
            Integer32,
        esIndexPC
            Integer32,
        esIndexPoint
            Integer32,
        esPointName
            DisplayString,
        esPointInEventState
            Integer32,
        esPointValueInt
            Integer32,
        esPointValueStr
            DisplayString,
        esPointTimeLastChange
            DisplayString,
        esPointTimetickLastChange
            TimeTicks,
        esPointAliasValueStr
            DisplayString
}

ESExist ::=
    SEQUENCE {
        esIndex
            Integer32,
        esName
            DisplayString,
        esID
            DisplayString,
        esNumberTempSensors
            Integer32,
        esTempReportingMode
            DisplayString,
        esNumberCCs
            Integer32,
        esCCReportingMode
            DisplayString,
        esNumberHumidSensors
            Integer32,
        esHumidReportingMode
            DisplayString,
        esNumberNoiseSensors
            Integer32,
        esNoiseReportingMode
            DisplayString,
        esNumberAirflowSensors
            Integer32,
        esAirflowReportingMode
            DisplayString,
        esNumberAnalog
            Integer32,
        esAnalogReportingMode
            DisplayString,
        esNumberRelayOutputs
            Integer32,
        esRelayReportingMode
            DisplayString,
        esTempCombinedStatus
            DisplayString,
        esCCCombinedStatusBlock1
            DisplayString,
        esCCCombinedStatusBlock2
            DisplayString,
        esCCCombinedStatusBlock3
            DisplayString,
        esCCCombinedStatusBlock4
            DisplayString,
        esCCCombinedStatusBlock5
            DisplayString,
        esCCCombinedStatusBlock6
            DisplayString,
        esCCCombinedStatusBlock7
            DisplayString,
        esCCCombinedStatusBlock8
            DisplayString,
        esHumidCombinedStatus
            DisplayString,
        esAnalogCombinedStatusBlock1
            DisplayString,
        esAnalogCombinedStatusBlock2
            DisplayString,
        esAnalogCombinedStatusBlock3
            DisplayString,
        esAnalogCombinedStatusBlock4
            DisplayString,
        esAnalogCombinedStatusBlock5
            DisplayString,
        esAnalogCombinedStatusBlock6
            DisplayString,
        esOutputCombinedStatusBlock1
            DisplayString,
        esOutputCombinedStatusBlock2
            DisplayString
}

DEStatus ::=
    SEQUENCE {
        deStatusIndex
            Integer32,
        deStatusName
            DisplayString,
        deStatusCounter
            Integer32,
        deStatusThreshold
            Integer32
}

FSStatus ::=
    SEQUENCE {
        fsStatusIndex
            Integer32,
        fsStatusName
            DisplayString,
        fsStatusDeviceState
            DisplayString,
        fsStatusVolumeValueString
            DisplayString,
        fsStatusVolumePercentLevel
            DisplayString,
        fsStatusVolumeInEventState
            DisplayString,
        fsStatusCombined
            DisplayString
}

ACPMStatus ::=
    SEQUENCE {
        acpmsIndex
            Integer32,
        acpmsName
            DisplayString,
        acpmsAvgVoltageValueStr
            DisplayString,
        acpmsAvgVoltageMinStr
            DisplayString,
        acpmsAvgVoltageMaxStr
            DisplayString,
        acpmsAvgVoltageAvgStr
            DisplayString,
        acpmsAvgVoltageInEventState
            DisplayString,
        acpmsVoltagePhaseAValueStr
            DisplayString,
        acpmsVoltagePhaseBValueStr
            DisplayString,
        acpmsVoltagePhaseCValueStr
            DisplayString,
        acpmsAvgCurrentValueStr
            DisplayString,
        acpmsAvgCurrentMinStr
            DisplayString,
        acpmsAvgCurrentMaxStr
            DisplayString,
        acpmsAvgCurrentAvgStr
            DisplayString,
        acpmsAvgCurrentInEventState
            DisplayString,
        acpmsCurrentPhaseAValueStr
            DisplayString,
        acpmsCurrentPhaseBValueStr
            DisplayString,
        acpmsCurrentPhaseCValueStr
            DisplayString,
        acpmsAvgFreqValueStr
            DisplayString,
        acpmsAvgFreqMinStr
            DisplayString,
        acpmsAvgFreqMaxStr
            DisplayString,
        acpmsAvgFreqAvgStr
            DisplayString,
        acpmsAvgFreqInEventState
            DisplayString,
        acpmsTRPValueStr
            DisplayString,
        acpmsTRPMinStr
            DisplayString,
        acpmsTRPMaxStr
            DisplayString,
        acpmsTRPAvgStr
            DisplayString,
        acpmsTRPInEventState
            DisplayString,
        acpmsRPPhaseAValueStr
            DisplayString,
        acpmsRPPhaseBValueStr
            DisplayString,
        acpmsRPPhaseCValueStr
            DisplayString,
        acpmsCombined
            DisplayString,
        acpmsTPFValueStr
            DisplayString,
        acpmsTPFMinStr
            DisplayString,
        acpmsTPFMaxStr
            DisplayString,
        acpmsTPFAvgStr
            DisplayString,
        acpmsTPFInEventState
            DisplayString,
        acpmsPFPhaseAValueStr
            DisplayString,
        acpmsPFPhaseBValueStr
            DisplayString,
        acpmsPFPhaseCValueStr
            DisplayString,
        acpmsTRcPValueStr
            DisplayString,
        acpmsTRcPMinStr
            DisplayString,
        acpmsTRcPMaxStr
            DisplayString,
        acpmsTRcPAvgStr
            DisplayString,
        acpmsRcPPhaseAValueStr
            DisplayString,
        acpmsRcPPhaseBValueStr
            DisplayString,
        acpmsRcPPhaseCValueStr
            DisplayString,
        acpmsTAPValueStr
            DisplayString,
        acpmsTAPMinStr
            DisplayString,
        acpmsTAPMaxStr
            DisplayString,
        acpmsTAPAvgStr
            DisplayString,
        acpmsAPPhaseAValueStr
            DisplayString,
        acpmsAPPhaseBValueStr
            DisplayString,
        acpmsAPPhaseCValueStr
            DisplayString,
        acpmsTotalEnergyWh
            Integer32,
        acpmsTotalEnergyVAR
            Integer32,
        acpmsTotalEnergyVA
            Integer32
}

ScheduleConfig ::=
    SEQUENCE {
        schedIndex
            Integer32,
        schedEnable
            DisplayString,
        schedStart
            DisplayString,
        schedRepeatMode
            DisplayString,
        schedRepeatFreq
            Integer32,
        schedRepeatEndMode
            DisplayString,
        schedRepeatEndAfter
            Integer32,
        schedRepeatEndOn
            DisplayString,
        schedRepeatWeeklySun
            DisplayString,
        schedRepeatWeeklyMon
            DisplayString,
        schedRepeatWeeklyTue
            DisplayString,
        schedRepeatWeeklyWed
            DisplayString,
        schedRepeatWeeklyThu
            DisplayString,
        schedRepeatWeeklyFri
            DisplayString,
        schedRepeatWeeklySat
            DisplayString,
        schedRepeatMonthlyMode
            DisplayString,
        schedRepeatMonthlyDates
            DisplayString,
        schedRepeatMonthlyOnThe
            DisplayString,
        schedRepeatMonthlyOnDay
            DisplayString,
        schedRepeatYearlyJan
            DisplayString,
        schedRepeatYearlyFeb
            DisplayString,
        schedRepeatYearlyMar
            DisplayString,
        schedRepeatYearlyApr
            DisplayString,
        schedRepeatYearlyMay
            DisplayString,
        schedRepeatYearlyJun
            DisplayString,
        schedRepeatYearlyJul
            DisplayString,
        schedRepeatYearlyAug
            DisplayString,
        schedRepeatYearlySep
            DisplayString,
        schedRepeatYearlyOct
            DisplayString,
        schedRepeatYearlyNov
            DisplayString,
        schedRepeatYearlyDec
            DisplayString,
        schedRepeatYearlyOnThe
            DisplayString,
        schedRepeatYearlyOnDay
            DisplayString,
        schedNextTrigger
            DisplayString
}

FuelSensorConfigGeneral ::=
    SEQUENCE {
        fsGenIndex
            Integer32,
        fsGenName
            DisplayString,
        fsGenSensorType
            DisplayString,
        fsGenDistanceUnit
            DisplayString,
        fsGenRawValueTop
            Integer32,
        fsGenTopOffset
            DisplayString,
        fsGenRawValueBottom
            Integer32,
        fsGenBottomOffset
            DisplayString,
        fsGenInputES
            Integer32,
        fsGenInputPoint
            Integer32,
        fsGenFilterAveraging
            Integer32,
        fsGenSysrepEnable
            DisplayString,
        fsGenSysrepThreshold
            DisplayString,
        fsGenSysrepLimit
            Integer32,
        fsGenSysrepPackage
            Integer32,
        fsGenSysrepType
            DisplayString
}

FuelSensorConfigTank ::=
    SEQUENCE {
        fsTankIndex
            Integer32,
        fsTankHeight
            DisplayString,
        fsTankDimA
            DisplayString,
        fsTankDimB
            DisplayString,
        fsTankVolume
            DisplayString,
        fsTankVolumeUnit
            DisplayString,
        fsTankShape
            DisplayString
}

FuelSensorConfigCustomTankStrapping ::=
    SEQUENCE {
        fsCustomTankIndexFS
            Integer32,
        fsCustomTankIndexDatum
            Integer32,
        fsCustomTankHeight
            DisplayString,
        fsCustomTankVolume
            DisplayString
}

FuelSensorConfigVolume ::=
    SEQUENCE {
        fsVolumeIndex
            Integer32,
        fsVolumeEnable
            DisplayString,
        fsVolumeDeadband
            DisplayString,
        fsVolumeVHighValue
            DisplayString,
        fsVolumeVHighActions
            DisplayString,
        fsVolumeVHighTrapNum
            Integer32,
        fsVolumeVHighClass
            DisplayString,
        fsVolumeHighValue
            DisplayString,
        fsVolumeHighActions
            DisplayString,
        fsVolumeHighTrapNum
            Integer32,
        fsVolumeHighClass
            DisplayString,
        fsVolumeNormalActions
            DisplayString,
        fsVolumeNormalTrapNum
            Integer32,
        fsVolumeNormalClass
            DisplayString,
        fsVolumeLowValue
            DisplayString,
        fsVolumeLowActions
            DisplayString,
        fsVolumeLowTrapNum
            Integer32,
        fsVolumeLowClass
            DisplayString,
        fsVolumeVLowValue
            DisplayString,
        fsVolumeVLowActions
            DisplayString,
        fsVolumeVLowTrapNum
            Integer32,
        fsVolumeVLowClass
            DisplayString
}

FuelSensorConfigDisconnect ::=
    SEQUENCE {
        fsDiscIndex
            Integer32,
        fsDiscEnable
            DisplayString,
        fsDiscHighValue
            Integer32,
        fsDiscLowValue
            Integer32,
        fsDiscActions
            DisplayString,
        fsDiscTrapNum
            Integer32,
        fsDiscClass
            DisplayString,
        fsDiscNormalActions
            DisplayString,
        fsDiscNormalTrapNum
            Integer32,
        fsDiscNormalClass
            DisplayString
}

FuelSensorConfigSuddenChange ::=
    SEQUENCE {
        fsSuddenChangeIndex
            Integer32,
        fsSuddenChangeEnable
            DisplayString,
        fsSuddenChangeTime
            Integer32,
        fsSuddenChangeAmplitude
            DisplayString,
        fsSuddenChangeActions
            DisplayString,
        fsSuddenChangeTrapNum
            Integer32,
        fsSuddenChangeClass
            DisplayString
}

FuelSensorConfigSlowChange ::=
    SEQUENCE {
        fsSlowChangeIndex
            Integer32,
        fsSlowChangeEnable
            DisplayString,
        fsSlowChangeTime
            Integer32,
        fsSlowChangeAmplitude
            DisplayString,
        fsSlowChangeActions
            DisplayString,
        fsSlowChangeTrapNum
            Integer32,
        fsSlowChangeClass
            DisplayString
}

ACPMConfigGeneral ::=
    SEQUENCE {
        acpmGenIndex
            Integer32,
        acpmGenDevice
            DisplayString,
        acpmGenName
            DisplayString,
        acpmGenAddress
            Integer32,
        acpmGenPtRatio
            Integer32,
        acpmGenCtRatio
            Integer32,
        acpmGenPowerType
            DisplayString,
        acpmGenSysrepPackage
            Integer32,
        acpmGenSysrepType
            DisplayString
}

ACPMConfigAvgVoltage ::=
    SEQUENCE {
        acpmAvgVoltageIndex
            Integer32,
        acpmAvgVoltageEnable
            DisplayString,
        acpmAvgVoltageDeadband
            DisplayString,
        acpmAvgVoltageVHighValue
            DisplayString,
        acpmAvgVoltageVHighActions
            DisplayString,
        acpmAvgVoltageVHighTrapNum
            Integer32,
        acpmAvgVoltageVHighClass
            DisplayString,
        acpmAvgVoltageHighValue
            DisplayString,
        acpmAvgVoltageHighActions
            DisplayString,
        acpmAvgVoltageHighTrapNum
            Integer32,
        acpmAvgVoltageHighClass
            DisplayString,
        acpmAvgVoltageNormalActions
            DisplayString,
        acpmAvgVoltageNormalTrapNum
            Integer32,
        acpmAvgVoltageNormalClass
            DisplayString,
        acpmAvgVoltageLowValue
            DisplayString,
        acpmAvgVoltageLowActions
            DisplayString,
        acpmAvgVoltageLowTrapNum
            Integer32,
        acpmAvgVoltageLowClass
            DisplayString,
        acpmAvgVoltageVLowValue
            DisplayString,
        acpmAvgVoltageVLowActions
            DisplayString,
        acpmAvgVoltageVLowTrapNum
            Integer32,
        acpmAvgVoltageVLowClass
            DisplayString,
        acpmAvgVoltageSysrepEnable
            DisplayString,
        acpmAvgVoltageSysrepThreshold
            DisplayString,
        acpmAvgVoltageSysrepLimit
            Integer32
}

ACPMConfigAvgCurrent ::=
    SEQUENCE {
        acpmAvgCurrentIndex
            Integer32,
        acpmAvgCurrentEnable
            DisplayString,
        acpmAvgCurrentDeadband
            DisplayString,
        acpmAvgCurrentVHighValue
            DisplayString,
        acpmAvgCurrentVHighActions
            DisplayString,
        acpmAvgCurrentVHighTrapNum
            Integer32,
        acpmAvgCurrentVHighClass
            DisplayString,
        acpmAvgCurrentHighValue
            DisplayString,
        acpmAvgCurrentHighActions
            DisplayString,
        acpmAvgCurrentHighTrapNum
            Integer32,
        acpmAvgCurrentHighClass
            DisplayString,
        acpmAvgCurrentNormalActions
            DisplayString,
        acpmAvgCurrentNormalTrapNum
            Integer32,
        acpmAvgCurrentNormalClass
            DisplayString,
        acpmAvgCurrentLowValue
            DisplayString,
        acpmAvgCurrentLowActions
            DisplayString,
        acpmAvgCurrentLowTrapNum
            Integer32,
        acpmAvgCurrentLowClass
            DisplayString,
        acpmAvgCurrentVLowValue
            DisplayString,
        acpmAvgCurrentVLowActions
            DisplayString,
        acpmAvgCurrentVLowTrapNum
            Integer32,
        acpmAvgCurrentVLowClass
            DisplayString,
        acpmAvgCurrentSysrepEnable
            DisplayString,
        acpmAvgCurrentSysrepThreshold
            DisplayString,
        acpmAvgCurrentSysrepLimit
            Integer32
}

ACPMConfigFreq ::=
    SEQUENCE {
        acpmFreqIndex
            Integer32,
        acpmFreqEnable
            DisplayString,
        acpmFreqDeadband
            DisplayString,
        acpmFreqVHighValue
            DisplayString,
        acpmFreqVHighActions
            DisplayString,
        acpmFreqVHighTrapNum
            Integer32,
        acpmFreqVHighClass
            DisplayString,
        acpmFreqHighValue
            DisplayString,
        acpmFreqHighActions
            DisplayString,
        acpmFreqHighTrapNum
            Integer32,
        acpmFreqHighClass
            DisplayString,
        acpmFreqNormalActions
            DisplayString,
        acpmFreqNormalTrapNum
            Integer32,
        acpmFreqNormalClass
            DisplayString,
        acpmFreqLowValue
            DisplayString,
        acpmFreqLowActions
            DisplayString,
        acpmFreqLowTrapNum
            Integer32,
        acpmFreqLowClass
            DisplayString,
        acpmFreqVLowValue
            DisplayString,
        acpmFreqVLowActions
            DisplayString,
        acpmFreqVLowTrapNum
            Integer32,
        acpmFreqVLowClass
            DisplayString,
        acpmFreqSysrepEnable
            DisplayString,
        acpmFreqSysrepThreshold
            DisplayString,
        acpmFreqSysrepLimit
            Integer32
}

ACPMConfigTRP ::=
    SEQUENCE {
        acpmTRPIndex
            Integer32,
        acpmTRPEnable
            DisplayString,
        acpmTRPDeadband
            DisplayString,
        acpmTRPVHighValue
            DisplayString,
        acpmTRPVHighActions
            DisplayString,
        acpmTRPVHighTrapNum
            Integer32,
        acpmTRPVHighClass
            DisplayString,
        acpmTRPHighValue
            DisplayString,
        acpmTRPHighActions
            DisplayString,
        acpmTRPHighTrapNum
            Integer32,
        acpmTRPHighClass
            DisplayString,
        acpmTRPNormalActions
            DisplayString,
        acpmTRPNormalTrapNum
            Integer32,
        acpmTRPNormalClass
            DisplayString,
        acpmTRPLowValue
            DisplayString,
        acpmTRPLowActions
            DisplayString,
        acpmTRPLowTrapNum
            Integer32,
        acpmTRPLowClass
            DisplayString,
        acpmTRPVLowValue
            DisplayString,
        acpmTRPVLowActions
            DisplayString,
        acpmTRPVLowTrapNum
            Integer32,
        acpmTRPVLowClass
            DisplayString,
        acpmTRPSysrepEnable
            DisplayString,
        acpmTRPSysrepThreshold
            DisplayString,
        acpmTRPSysrepLimit
            Integer32
}

ACPMConfigDisconnect ::=
    SEQUENCE {
        acpmDisconnectIndex
            Integer32,
        acpmDisconnectEnable
            DisplayString,
        acpmDisconnectActions
            DisplayString,
        acpmDisconnectTrapNum
            Integer32,
        acpmDisconnectClass
            DisplayString,
        acpmDisconnectNormalActions
            DisplayString,
        acpmDisconnectNormalTrapNum
            Integer32,
        acpmDisconnectNormalClass
            DisplayString
}

ACPMConfigTotalPowerFactor ::=
    SEQUENCE {
        acpmTPFIndex
            Integer32,
        acpmTPFEnable
            DisplayString,
        acpmTPFDeadband
            DisplayString,
        acpmTPFNormalActions
            DisplayString,
        acpmTPFNormalTrapNum
            Integer32,
        acpmTPFNormalClass
            DisplayString,
        acpmTPFLowValue
            DisplayString,
        acpmTPFLowActions
            DisplayString,
        acpmTPFLowTrapNum
            Integer32,
        acpmTPFLowClass
            DisplayString,
        acpmTPFVLowValue
            DisplayString,
        acpmTPFVLowActions
            DisplayString,
        acpmTPFVLowTrapNum
            Integer32,
        acpmTPFVLowClass
            DisplayString,
        acpmTPFSysrepEnable
            DisplayString,
        acpmTPFSysrepThreshold
            DisplayString,
        acpmTPFSysrepLimit
            Integer32
}


BatteryMonitorConfigGeneral ::=
    SEQUENCE {
        bmGenIndex
            Integer32,
        bmGenEnable
            DisplayString,
        bmGenName
            DisplayString,
        bmGenBatteryQuantity
            Integer32,
        bmGenBatteryCapacity
            Integer32,
        bmGenBatteryNominalVoltage
            DisplayString,
        bmGenSysrepPackage
            Integer32,
        bmGenSysrepType
            DisplayString
}

BatteryMonitorConfigDevice ::=
    SEQUENCE {
        bmDeviceIndex
            Integer32,
        bmDeviceType
            DisplayString,
        bmDeviceES
            Integer32,
        bmDeviceIP
            IpAddress,
        bmDeviceReadcom
            DisplayString,
        bmDeviceInputString
            Integer32,
        bmDeviceCTSize
            Integer32
}

BatteryMonitorConfigTemp ::=
    SEQUENCE {
        bmTempIndex
            Integer32,
        bmTempEnable
            DisplayString,
        bmTempDeadband
            DisplayString,
        bmTempScale
            DisplayString,
        bmTempHighValue
            DisplayString,
        bmTempHighActions
            DisplayString,
        bmTempHighTrapNum
            Integer32,
        bmTempHighClass
            DisplayString,
        bmTempNormalActions
            DisplayString,
        bmTempNormalTrapNum
            Integer32,
        bmTempNormalClass
            DisplayString,
        bmTempLowValue
            DisplayString,
        bmTempLowActions
            DisplayString,
        bmTempLowTrapNum
            Integer32,
        bmTempLowClass
            DisplayString,
        bmTempSysrepEnable
            DisplayString,
        bmTempSysrepThreshold
            DisplayString,
        bmTempSysrepLimit
            Integer32
}

BatteryMonitorConfigDiffTemp ::=
    SEQUENCE {
        bmDiffTempIndex
            Integer32,
        bmDiffTempEnable
            DisplayString,
        bmDiffTempDeadband
            Integer32,
        bmDiffTempVHighValue
            Integer32,
        bmDiffTempVHighActions
            DisplayString,
        bmDiffTempVHighTrapNum
            Integer32,
        bmDiffTempVHighClass
            DisplayString,
        bmDiffTempHighValue
            Integer32,
        bmDiffTempHighActions
            DisplayString,
        bmDiffTempHighTrapNum
            Integer32,
        bmDiffTempHighClass
            DisplayString,
        bmDiffTempNormalActions
            DisplayString,
        bmDiffTempNormalTrapNum
            Integer32,
        bmDiffTempNormalClass
            DisplayString,
        bmDiffTempSysrepEnable
            DisplayString,
        bmDiffTempSysrepThreshold
            Integer32,
        bmDiffTempSysrepLimit
            Integer32
}

BatteryMonitorConfigVoltage ::=
    SEQUENCE {
        bmVoltageIndex
            Integer32,
        bmVoltageEnable
            DisplayString,
        bmVoltageDeadband
            DisplayString,
        bmVoltageVHighValue
            DisplayString,
        bmVoltageVHighActions
            DisplayString,
        bmVoltageVHighTrapNum
            Integer32,
        bmVoltageVHighClass
            DisplayString,
        bmVoltageHighValue
            DisplayString,
        bmVoltageHighActions
            DisplayString,
        bmVoltageHighTrapNum
            Integer32,
        bmVoltageHighClass
            DisplayString,
        bmVoltageNormalActions
            DisplayString,
        bmVoltageNormalTrapNum
            Integer32,
        bmVoltageNormalClass
            DisplayString,
        bmVoltageLowValue
            DisplayString,
        bmVoltageLowActions
            DisplayString,
        bmVoltageLowTrapNum
            Integer32,
        bmVoltageLowClass
            DisplayString,
        bmVoltageVLowValue
            DisplayString,
        bmVoltageVLowActions
            DisplayString,
        bmVoltageVLowTrapNum
            Integer32,
        bmVoltageVLowClass
            DisplayString,
        bmVoltageSysrepEnable
            DisplayString,
        bmVoltageSysrepThreshold
            DisplayString,
        bmVoltageSysrepLimit
            Integer32
}

BatteryMonitorConfigDiffVolt ::=
    SEQUENCE {
        bmDiffVoltIndex
            Integer32,
        bmDiffVoltEnable
            DisplayString,
        bmDiffVoltDeadband
            DisplayString,
        bmDiffVoltVHighValue
            DisplayString,
        bmDiffVoltVHighActions
            DisplayString,
        bmDiffVoltVHighTrapNum
            Integer32,
        bmDiffVoltVHighClass
            DisplayString,
        bmDiffVoltHighValue
            DisplayString,
        bmDiffVoltHighActions
            DisplayString,
        bmDiffVoltHighTrapNum
            Integer32,
        bmDiffVoltHighClass
            DisplayString,
        bmDiffVoltNormalActions
            DisplayString,
        bmDiffVoltNormalTrapNum
            Integer32,
        bmDiffVoltNormalClass
            DisplayString,
        bmDiffVoltSysrepEnable
            DisplayString,
        bmDiffVoltSysrepThreshold
            DisplayString,
        bmDiffVoltSysrepLimit
            Integer32
}

BatteryMonitorConfigChargingCurrent ::=
    SEQUENCE {
        bmChargingCurrentIndex
            Integer32,
        bmChargingCurrentEnable
            DisplayString,
        bmChargingCurrentDeadband
            DisplayString,
        bmChargingCurrentVHighValue
            DisplayString,
        bmChargingCurrentVHighActions
            DisplayString,
        bmChargingCurrentVHighTrapNum
            Integer32,
        bmChargingCurrentVHighClass
            DisplayString,
        bmChargingCurrentHighValue
            DisplayString,
        bmChargingCurrentHighActions
            DisplayString,
        bmChargingCurrentHighTrapNum
            Integer32,
        bmChargingCurrentHighClass
            DisplayString,
        bmChargingCurrentNormalActions
            DisplayString,
        bmChargingCurrentNormalTrapNum
            Integer32,
        bmChargingCurrentNormalClass
            DisplayString,
        bmChargingCurrentSysrepEnable
            DisplayString,
        bmChargingCurrentSysrepThreshold
            DisplayString,
        bmChargingCurrentSysrepLimit
            Integer32
}

BatteryMonitorConfigDischargingCurrent ::=
    SEQUENCE {
        bmDischargingCurrentIndex
            Integer32,
        bmDischargingCurrentEnable
            DisplayString,
        bmDischargingCurrentDeadband
            DisplayString,
        bmDischargingCurrentVHighValue
            DisplayString,
        bmDischargingCurrentVHighActions
            DisplayString,
        bmDischargingCurrentVHighTrapNum
            Integer32,
        bmDischargingCurrentVHighClass
            DisplayString,
        bmDischargingCurrentHighValue
            DisplayString,
        bmDischargingCurrentHighActions
            DisplayString,
        bmDischargingCurrentHighTrapNum
            Integer32,
        bmDischargingCurrentHighClass
            DisplayString,
        bmDischargingCurrentNormalActions
            DisplayString,
        bmDischargingCurrentNormalTrapNum
            Integer32,
        bmDischargingCurrentNormalClass
            DisplayString,
        bmDischargingCurrentSysrepEnable
            DisplayString,
        bmDischargingCurrentSysrepThreshold
            DisplayString,
        bmDischargingCurrentSysrepLimit
            Integer32
}

BatteryMonitorConfigChargeLevel ::=
    SEQUENCE {
        bmChargeLevelIndex
            Integer32,
        bmChargeLevelEnable
            DisplayString,
        bmChargeLevelNormalActions
            DisplayString,
        bmChargeLevelNormalTrapNum
            Integer32,
        bmChargeLevelNormalClass
            DisplayString,
        bmChargeLevelLowActions
            DisplayString,
        bmChargeLevelLowTrapNum
            Integer32,
        bmChargeLevelLowClass
            DisplayString,
        bmChargeLevelVLowActions
            DisplayString,
        bmChargeLevelVLowTrapNum
            Integer32,
        bmChargeLevelVLowClass
            DisplayString,
        bmChargeLevelSysrepEnable
            DisplayString
}

BatteryMonitorConfigJarHealth ::=
    SEQUENCE {
        bmJarHealthIndex
            Integer32,
        bmJarHealthEnable
            DisplayString,
        bmJarHealthNormalActions
            DisplayString,
        bmJarHealthNormalTrapNum
            Integer32,
        bmJarHealthNormalClass
            DisplayString,
        bmJarHealthLowActions
            DisplayString,
        bmJarHealthLowTrapNum
            Integer32,
        bmJarHealthLowClass
            DisplayString,
        bmJarHealthVLowActions
            DisplayString,
        bmJarHealthVLowTrapNum
            Integer32,
        bmJarHealthVLowClass
            DisplayString,
        bmJarHealthSysrepEnable
            DisplayString
}



BMStatus ::=
    SEQUENCE {
        bmsIndex
            Integer32,
        bmsEnable
            DisplayString,
        bmsName
            DisplayString,
        bmsState
            DisplayString,
        bmsStringState
            DisplayString,
        bmsTempValue
            DisplayString,
        bmsTempValueStr
            DisplayString,
        bmsTempEvent
            DisplayString,
        bmsDiffTempValue
            Integer32,
        bmsDiffTempValueStr
            DisplayString,
        bmsDiffTempEvent
            DisplayString,
        bmsVoltageValue
            DisplayString,
        bmsVoltageEvent
            DisplayString,
        bmsDiffVoltValue
            DisplayString,
        bmsDiffVoltEvent
            DisplayString,
        bmsCurrentValue
            DisplayString,
        bmsChargingCurrentEvent
            DisplayString,
        bmsDischargingCurrentEvent
            DisplayString,
        bmsChargeLevelValue
            DisplayString,
        bmsChargeLevelEvent
            DisplayString,
        bmsJarHealthValue
            DisplayString,
        bmsJarHealthEvent
            DisplayString,
        bmsCombined
            DisplayString
}

BMJarStatus ::=
    SEQUENCE {
        bmjsIndexBM
            Integer32,
        bmjsIndexJar
            Integer32,
        bmjsVoltageValue
            DisplayString,
        bmjsTempValue
            DisplayString,
        bmjsAdmittanceValue
            Integer32,
        bmjsAdmittanceChangeValue
            Integer32
}

--***************************************************************************************
--TRAP DEFINITIONS
--***************************************************************************************

s450StockContactClosureTrap NOTIFICATION-TYPE
    OBJECTS { siteName, stockTrapString, trapTypeString }
    STATUS current
    DESCRIPTION
        "A stock contact closure trap is issued when a contact closure
        event happens."
    ::= { s450notifications 110 }

s450StockTempTrap NOTIFICATION-TYPE
    OBJECTS { siteName, stockTrapString, trapTypeString }
    STATUS current
    DESCRIPTION
        "A stock temperature trap is issued when a temperature event
        happens."
    ::= { s450notifications 120 }

s450StockHumidityTrap NOTIFICATION-TYPE
    OBJECTS { siteName, stockTrapString, trapTypeString }
    STATUS current
    DESCRIPTION
        "A stock humidity trap is issued when a humidity event
        happens."
    ::= { s450notifications 130 }

s450StockAnalogTrap NOTIFICATION-TYPE
    OBJECTS { siteName, stockTrapString, trapTypeString }
    STATUS current
    DESCRIPTION
        "A stock analog trap is issued when an analog sensor event
        happens."
    ::= { s450notifications 140 }

s450StockOutputTrap NOTIFICATION-TYPE
    OBJECTS { siteName, stockTrapString, trapTypeString }
    STATUS current
    DESCRIPTION
        "A stock output trap is issued when an output event
        happens.  That is, depending on the configuration,
        when an output changes state for any reason, this
        trap will be sent."
    ::= { s450notifications 150 }

s450StockSchedTrap NOTIFICATION-TYPE
    OBJECTS { siteName, stockTrapString, trapTypeString }
    STATUS current
    DESCRIPTION
        "The stock scheduled alarm trap is issued
        when the current time reaches the scheduled
        alarm time."
    ::= { s450notifications 506 }

s450StockImmediateTrap NOTIFICATION-TYPE
    OBJECTS { siteName, stockTrapString, trapTypeString }
    STATUS current
    DESCRIPTION
        "The stock immediate alarm trap is issued
        when the user enters the DOTRAP command."
    ::= { s450notifications 507 }

s450StockCTSTrap  NOTIFICATION-TYPE
    OBJECTS { siteName, stockTrapString, trapTypeString }
    STATUS current
    DESCRIPTION
        "A stock CTS trap is issued when an RS-232 CTS event
        happens."
    ::= { s450notifications 510 }

s450CPEDownTrap  NOTIFICATION-TYPE
    OBJECTS { siteName, stockTrapString, trapTypeString }
    STATUS current
    DESCRIPTION
        "A stock CPE Down trap is issued when a CPE Down event
        happens."
    ::= { s450notifications 511 }

s450FuelSensorDisconnectTrap  NOTIFICATION-TYPE
    OBJECTS { siteName, stockTrapString, trapTypeString }
    STATUS current
    DESCRIPTION
        "A stock Fuel Sensor Disconnect trap is issued when a Fuel
        Sensor Disconnect or Connect (Return to Normal) event happens."
    ::= { s450notifications 515 }

s450FuelSensorVolumeTrap  NOTIFICATION-TYPE
    OBJECTS { siteName, stockTrapString, trapTypeString }
    STATUS current
    DESCRIPTION
        "A stock Fuel Sensor Volume trap is issued when a Fuel
        Sensor Volume event happens"
    ::= { s450notifications 519 }

s450ACPowerMonitorAvgVoltageTrap  NOTIFICATION-TYPE
    OBJECTS { siteName, stockTrapString, trapTypeString }
    STATUS current
    DESCRIPTION
        "A stock AC power monitor average voltage trap is issued when an
        AC power monitor average voltage event happens."
    ::= { s450notifications 520 }

s450ACPowerMonitorAvgCurrentTrap  NOTIFICATION-TYPE
    OBJECTS { siteName, stockTrapString, trapTypeString }
    STATUS current
    DESCRIPTION
        "A stock AC power monitor average current trap is issued when an
        AC power monitor average current event happens."
    ::= { s450notifications 521 }

s450ACPowerMonitorFrequencyTrap  NOTIFICATION-TYPE
    OBJECTS { siteName, stockTrapString, trapTypeString }
    STATUS current
    DESCRIPTION
        "A stock AC power monitor frequency trap is issued when an
        AC power monitor frequency event happens."
    ::= { s450notifications 522 }

s450ACPowerMonitorTRPTrap  NOTIFICATION-TYPE
    OBJECTS { siteName, stockTrapString, trapTypeString }
    STATUS current
    DESCRIPTION
        "A stock AC power monitor TRP (total real power) trap is issued
        when an AC power monitor TRP event happens."
    ::= { s450notifications 523 }

s450ACPowerMonitorDisconnectTrap  NOTIFICATION-TYPE
    OBJECTS { siteName, stockTrapString, trapTypeString }
    STATUS current
    DESCRIPTION
        "A stock AC power monitor disconnect trap is issued
        when an AC power monitor disconnect event happens."
    ::= { s450notifications 524 }

s450StockScriptTrap  NOTIFICATION-TYPE
    OBJECTS { siteName, stockTrapString, trapTypeString }
    STATUS current
    DESCRIPTION
        "A stock script trap is issued when a script triggers
        an event via a_lib.PostEvent() called with no trap
        number (or this trap number) specified."
    ::= { s450notifications 526 }

s450FuelSensorVolumeSuddenChangeTrap  NOTIFICATION-TYPE
    OBJECTS { siteName, stockTrapString, trapTypeString }
    STATUS current
    DESCRIPTION
        "A stock Fuel Sensor Volume Sudden Change trap is issued
        when a Fuel Sensor Volume Sudden Change event happens"
    ::= { s450notifications 527 }

s450FuelSensorVolumeSlowChangeTrap  NOTIFICATION-TYPE
    OBJECTS { siteName, stockTrapString, trapTypeString }
    STATUS current
    DESCRIPTION
        "A stock Fuel Sensor Volume Slow Change trap is issued
        when a Fuel Sensor Volume Slow Change event happens"
    ::= { s450notifications 528 }

s450BattMonStringTemperatureTrap  NOTIFICATION-TYPE
    OBJECTS { siteName, stockTrapString, trapTypeString }
    STATUS current
    DESCRIPTION
        "A stock Battery Monitor String Temperature trap is issued
        when a Battery Monitor String Temperature event happens."
    ::= { s450notifications 530 }

s450BattMonStringDiffTemperatureTrap  NOTIFICATION-TYPE
    OBJECTS { siteName, stockTrapString, trapTypeString }
    STATUS current
    DESCRIPTION
        "A stock Battery Monitor String Differential Temperature
        trap is issued when a Battery Monitor String Differential
        Temperature event happens."
    ::= { s450notifications 531 }

s450BattMonStringVoltageTrap  NOTIFICATION-TYPE
    OBJECTS { siteName, stockTrapString, trapTypeString }
    STATUS current
    DESCRIPTION
        "A stock Battery Monitor String Voltage trap is issued
        when a Battery Monitor String Voltage event happens."
    ::= { s450notifications 532 }

s450BattMonStringChargeLevelTrap  NOTIFICATION-TYPE
    OBJECTS { siteName, stockTrapString, trapTypeString }
    STATUS current
    DESCRIPTION
        "A stock Battery Monitor String Charge Level trap is issued
        when a Battery Monitor String Charge Level event happens."
    ::= { s450notifications 533 }

s450BattMonStringChargingCurrentTrap  NOTIFICATION-TYPE
    OBJECTS { siteName, stockTrapString, trapTypeString }
    STATUS current
    DESCRIPTION
        "A stock Battery Monitor String Charging Current trap is issued
        when a Battery Monitor String Charging Current event happens."
    ::= { s450notifications 534 }

s450BattMonStringDischargingCurrentTrap  NOTIFICATION-TYPE
    OBJECTS { siteName, stockTrapString, trapTypeString }
    STATUS current
    DESCRIPTION
        "A stock Battery Monitor String Discharging Current trap is issued
        when a Battery Monitor String Discharging Current event happens."
    ::= { s450notifications 535 }

s450GeneratorNonStartTrap  NOTIFICATION-TYPE
    OBJECTS { siteName, stockTrapString, trapTypeString }
    STATUS current
    DESCRIPTION
        "A stock Generator Non-start trap is issued
        when the unit commands the generator to start as
        part of the generator exercising feature, and the
        generator fails to register as started after 30
        seconds (as detected by CC generator running
        detection)."
    ::= { s450notifications 536 }

s450BattMonStringDifferentialVoltageTrap  NOTIFICATION-TYPE
    OBJECTS { siteName, stockTrapString, trapTypeString }
    STATUS current
    DESCRIPTION
        "A stock Battery Monitor String Differential Voltage trap is issued
        when a Battery Monitor String Differential Voltage event happens."
    ::= { s450notifications 537 }

s450BattMonStringJarHealthTrap  NOTIFICATION-TYPE
    OBJECTS { siteName, stockTrapString, trapTypeString }
    STATUS current
    DESCRIPTION
        "A stock Battery Monitor String Jar Health trap is issued
        when a Battery Monitor String Jar Health event happens."
    ::= { s450notifications 538 }

s450CameraTrap  NOTIFICATION-TYPE
    OBJECTS { siteName, stockTrapString, trapTypeString }
    STATUS current
    DESCRIPTION
        "A stock camera trap is issued when a camera event happens."
    ::= { s450notifications 539 }

s450ACTotalPowerFactorTrap  NOTIFICATION-TYPE
    OBJECTS { siteName, stockTrapString, trapTypeString }
    STATUS current
    DESCRIPTION
        "A stock AC power monitor total power factor trap is issued
        when an AC power monitor total power factor event happens."
    ::= { s450notifications 540 }

s450ResetTrap  NOTIFICATION-TYPE
    OBJECTS { siteName, stockTrapString, trapTypeString }
    STATUS current
    DESCRIPTION
        "A stock reset trap is issued when a reset event happens."
    ::= { s450notifications 543 }

s450UserTrap1000 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1000."
    ::= { s450notifications 1000 }

s450UserTrap1001 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1001."
    ::= { s450notifications 1001 }

s450UserTrap1002 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1002."
    ::= { s450notifications 1002 }

s450UserTrap1003 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1003."
    ::= { s450notifications 1003 }

s450UserTrap1004 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1004."
    ::= { s450notifications 1004 }

s450UserTrap1005 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1005."
    ::= { s450notifications 1005 }

s450UserTrap1006 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1006."
    ::= { s450notifications 1006 }

s450UserTrap1007 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1007."
    ::= { s450notifications 1007 }

s450UserTrap1008 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1008."
    ::= { s450notifications 1008 }

s450UserTrap1009 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1009."
    ::= { s450notifications 1009 }

s450UserTrap1010 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1010."
    ::= { s450notifications 1010 }

s450UserTrap1011 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1011."
    ::= { s450notifications 1011 }

s450UserTrap1012 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1012."
    ::= { s450notifications 1012 }

s450UserTrap1013 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1013."
    ::= { s450notifications 1013 }

s450UserTrap1014 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1014."
    ::= { s450notifications 1014 }

s450UserTrap1015 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1015."
    ::= { s450notifications 1015 }

s450UserTrap1016 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1016."
    ::= { s450notifications 1016 }

s450UserTrap1017 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1017."
    ::= { s450notifications 1017 }

s450UserTrap1018 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1018."
    ::= { s450notifications 1018 }

s450UserTrap1019 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1019."
    ::= { s450notifications 1019 }

s450UserTrap1020 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1020."
    ::= { s450notifications 1020 }

s450UserTrap1021 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1021."
    ::= { s450notifications 1021 }

s450UserTrap1022 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1022."
    ::= { s450notifications 1022 }

s450UserTrap1023 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1023."
    ::= { s450notifications 1023 }

s450UserTrap1024 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1024."
    ::= { s450notifications 1024 }

s450UserTrap1025 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1025."
    ::= { s450notifications 1025 }

s450UserTrap1026 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1026."
    ::= { s450notifications 1026 }

s450UserTrap1027 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1027."
    ::= { s450notifications 1027 }

s450UserTrap1028 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1028."
    ::= { s450notifications 1028 }

s450UserTrap1029 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1029."
    ::= { s450notifications 1029 }

s450UserTrap1030 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1030."
    ::= { s450notifications 1030 }

s450UserTrap1031 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1031."
    ::= { s450notifications 1031 }

s450UserTrap1032 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1032."
    ::= { s450notifications 1032 }

s450UserTrap1033 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1033."
    ::= { s450notifications 1033 }

s450UserTrap1034 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1034."
    ::= { s450notifications 1034 }

s450UserTrap1035 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1035."
    ::= { s450notifications 1035 }

s450UserTrap1036 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1036."
    ::= { s450notifications 1036 }

s450UserTrap1037 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1037."
    ::= { s450notifications 1037 }

s450UserTrap1038 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1038."
    ::= { s450notifications 1038 }

s450UserTrap1039 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1039."
    ::= { s450notifications 1039 }

s450UserTrap1040 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1040."
    ::= { s450notifications 1040 }

s450UserTrap1041 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1041."
    ::= { s450notifications 1041 }

s450UserTrap1042 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1042."
    ::= { s450notifications 1042 }

s450UserTrap1043 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1043."
    ::= { s450notifications 1043 }

s450UserTrap1044 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1044."
    ::= { s450notifications 1044 }

s450UserTrap1045 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1045."
    ::= { s450notifications 1045 }

s450UserTrap1046 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1046."
    ::= { s450notifications 1046 }

s450UserTrap1047 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1047."
    ::= { s450notifications 1047 }

s450UserTrap1048 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1048."
    ::= { s450notifications 1048 }

s450UserTrap1049 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1049."
    ::= { s450notifications 1049 }

s450UserTrap1050 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1050."
    ::= { s450notifications 1050 }

s450UserTrap1051 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1051."
    ::= { s450notifications 1051 }

s450UserTrap1052 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1052."
    ::= { s450notifications 1052 }

s450UserTrap1053 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1053."
    ::= { s450notifications 1053 }

s450UserTrap1054 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1054."
    ::= { s450notifications 1054 }

s450UserTrap1055 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1055."
    ::= { s450notifications 1055 }

s450UserTrap1056 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1056."
    ::= { s450notifications 1056 }

s450UserTrap1057 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1057."
    ::= { s450notifications 1057 }

s450UserTrap1058 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1058."
    ::= { s450notifications 1058 }

s450UserTrap1059 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1059."
    ::= { s450notifications 1059 }

s450UserTrap1060 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1060."
    ::= { s450notifications 1060 }

s450UserTrap1061 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1061."
    ::= { s450notifications 1061 }

s450UserTrap1062 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1062."
    ::= { s450notifications 1062 }

s450UserTrap1063 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1063."
    ::= { s450notifications 1063 }

s450UserTrap1064 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1064."
    ::= { s450notifications 1064 }

s450UserTrap1065 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1065."
    ::= { s450notifications 1065 }

s450UserTrap1066 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1066."
    ::= { s450notifications 1066 }

s450UserTrap1067 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1067."
    ::= { s450notifications 1067 }

s450UserTrap1068 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1068."
    ::= { s450notifications 1068 }

s450UserTrap1069 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1069."
    ::= { s450notifications 1069 }

s450UserTrap1070 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1070."
    ::= { s450notifications 1070 }

s450UserTrap1071 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1071."
    ::= { s450notifications 1071 }

s450UserTrap1072 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1072."
    ::= { s450notifications 1072 }

s450UserTrap1073 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1073."
    ::= { s450notifications 1073 }

s450UserTrap1074 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1074."
    ::= { s450notifications 1074 }

s450UserTrap1075 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1075."
    ::= { s450notifications 1075 }

s450UserTrap1076 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1076."
    ::= { s450notifications 1076 }

s450UserTrap1077 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1077."
    ::= { s450notifications 1077 }

s450UserTrap1078 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1078."
    ::= { s450notifications 1078 }

s450UserTrap1079 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1079."
    ::= { s450notifications 1079 }

s450UserTrap1080 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1080."
    ::= { s450notifications 1080 }

s450UserTrap1081 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1081."
    ::= { s450notifications 1081 }

s450UserTrap1082 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1082."
    ::= { s450notifications 1082 }

s450UserTrap1083 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1083."
    ::= { s450notifications 1083 }

s450UserTrap1084 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1084."
    ::= { s450notifications 1084 }

s450UserTrap1085 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1085."
    ::= { s450notifications 1085 }

s450UserTrap1086 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1086."
    ::= { s450notifications 1086 }

s450UserTrap1087 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1087."
    ::= { s450notifications 1087 }

s450UserTrap1088 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1088."
    ::= { s450notifications 1088 }

s450UserTrap1089 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1089."
    ::= { s450notifications 1089 }

s450UserTrap1090 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1090."
    ::= { s450notifications 1090 }

s450UserTrap1091 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1091."
    ::= { s450notifications 1091 }

s450UserTrap1092 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1092."
    ::= { s450notifications 1092 }

s450UserTrap1093 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1093."
    ::= { s450notifications 1093 }

s450UserTrap1094 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1094."
    ::= { s450notifications 1094 }

s450UserTrap1095 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1095."
    ::= { s450notifications 1095 }

s450UserTrap1096 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1096."
    ::= { s450notifications 1096 }

s450UserTrap1097 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1097."
    ::= { s450notifications 1097 }

s450UserTrap1098 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1098."
    ::= { s450notifications 1098 }

s450UserTrap1099 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1099."
    ::= { s450notifications 1099 }

s450UserTrap1100 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1100."
    ::= { s450notifications 1100 }

s450UserTrap1101 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1101."
    ::= { s450notifications 1101 }

s450UserTrap1102 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1102."
    ::= { s450notifications 1102 }

s450UserTrap1103 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1103."
    ::= { s450notifications 1103 }

s450UserTrap1104 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1104."
    ::= { s450notifications 1104 }

s450UserTrap1105 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1105."
    ::= { s450notifications 1105 }

s450UserTrap1106 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1106."
    ::= { s450notifications 1106 }

s450UserTrap1107 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1107."
    ::= { s450notifications 1107 }

s450UserTrap1108 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1108."
    ::= { s450notifications 1108 }

s450UserTrap1109 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1109."
    ::= { s450notifications 1109 }

s450UserTrap1110 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1110."
    ::= { s450notifications 1110 }

s450UserTrap1111 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1111."
    ::= { s450notifications 1111 }

s450UserTrap1112 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1112."
    ::= { s450notifications 1112 }

s450UserTrap1113 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1113."
    ::= { s450notifications 1113 }

s450UserTrap1114 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1114."
    ::= { s450notifications 1114 }

s450UserTrap1115 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1115."
    ::= { s450notifications 1115 }

s450UserTrap1116 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1116."
    ::= { s450notifications 1116 }

s450UserTrap1117 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1117."
    ::= { s450notifications 1117 }

s450UserTrap1118 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1118."
    ::= { s450notifications 1118 }

s450UserTrap1119 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1119."
    ::= { s450notifications 1119 }

s450UserTrap1120 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1120."
    ::= { s450notifications 1120 }

s450UserTrap1121 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1121."
    ::= { s450notifications 1121 }

s450UserTrap1122 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1122."
    ::= { s450notifications 1122 }

s450UserTrap1123 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1123."
    ::= { s450notifications 1123 }

s450UserTrap1124 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1124."
    ::= { s450notifications 1124 }

s450UserTrap1125 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1125."
    ::= { s450notifications 1125 }

s450UserTrap1126 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1126."
    ::= { s450notifications 1126 }

s450UserTrap1127 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1127."
    ::= { s450notifications 1127 }

s450UserTrap1128 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1128."
    ::= { s450notifications 1128 }

s450UserTrap1129 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1129."
    ::= { s450notifications 1129 }

s450UserTrap1130 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1130."
    ::= { s450notifications 1130 }

s450UserTrap1131 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1131."
    ::= { s450notifications 1131 }

s450UserTrap1132 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1132."
    ::= { s450notifications 1132 }

s450UserTrap1133 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1133."
    ::= { s450notifications 1133 }

s450UserTrap1134 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1134."
    ::= { s450notifications 1134 }

s450UserTrap1135 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1135."
    ::= { s450notifications 1135 }

s450UserTrap1136 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1136."
    ::= { s450notifications 1136 }

s450UserTrap1137 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1137."
    ::= { s450notifications 1137 }

s450UserTrap1138 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1138."
    ::= { s450notifications 1138 }

s450UserTrap1139 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1139."
    ::= { s450notifications 1139 }

s450UserTrap1140 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1140."
    ::= { s450notifications 1140 }

s450UserTrap1141 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1141."
    ::= { s450notifications 1141 }

s450UserTrap1142 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1142."
    ::= { s450notifications 1142 }

s450UserTrap1143 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1143."
    ::= { s450notifications 1143 }

s450UserTrap1144 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1144."
    ::= { s450notifications 1144 }

s450UserTrap1145 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1145."
    ::= { s450notifications 1145 }

s450UserTrap1146 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1146."
    ::= { s450notifications 1146 }

s450UserTrap1147 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1147."
    ::= { s450notifications 1147 }

s450UserTrap1148 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1148."
    ::= { s450notifications 1148 }

s450UserTrap1149 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1149."
    ::= { s450notifications 1149 }

s450UserTrap1150 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1150."
    ::= { s450notifications 1150 }

s450UserTrap1151 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1151."
    ::= { s450notifications 1151 }

s450UserTrap1152 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1152."
    ::= { s450notifications 1152 }

s450UserTrap1153 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1153."
    ::= { s450notifications 1153 }

s450UserTrap1154 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1154."
    ::= { s450notifications 1154 }

s450UserTrap1155 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1155."
    ::= { s450notifications 1155 }

s450UserTrap1156 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1156."
    ::= { s450notifications 1156 }

s450UserTrap1157 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1157."
    ::= { s450notifications 1157 }

s450UserTrap1158 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1158."
    ::= { s450notifications 1158 }

s450UserTrap1159 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1159."
    ::= { s450notifications 1159 }

s450UserTrap1160 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1160."
    ::= { s450notifications 1160 }

s450UserTrap1161 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1161."
    ::= { s450notifications 1161 }

s450UserTrap1162 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1162."
    ::= { s450notifications 1162 }

s450UserTrap1163 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1163."
    ::= { s450notifications 1163 }

s450UserTrap1164 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1164."
    ::= { s450notifications 1164 }

s450UserTrap1165 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1165."
    ::= { s450notifications 1165 }

s450UserTrap1166 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1166."
    ::= { s450notifications 1166 }

s450UserTrap1167 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1167."
    ::= { s450notifications 1167 }

s450UserTrap1168 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1168."
    ::= { s450notifications 1168 }

s450UserTrap1169 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1169."
    ::= { s450notifications 1169 }

s450UserTrap1170 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1170."
    ::= { s450notifications 1170 }

s450UserTrap1171 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1171."
    ::= { s450notifications 1171 }

s450UserTrap1172 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1172."
    ::= { s450notifications 1172 }

s450UserTrap1173 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1173."
    ::= { s450notifications 1173 }

s450UserTrap1174 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1174."
    ::= { s450notifications 1174 }

s450UserTrap1175 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1175."
    ::= { s450notifications 1175 }

s450UserTrap1176 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1176."
    ::= { s450notifications 1176 }

s450UserTrap1177 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1177."
    ::= { s450notifications 1177 }

s450UserTrap1178 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1178."
    ::= { s450notifications 1178 }

s450UserTrap1179 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1179."
    ::= { s450notifications 1179 }

s450UserTrap1180 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1180."
    ::= { s450notifications 1180 }

s450UserTrap1181 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1181."
    ::= { s450notifications 1181 }

s450UserTrap1182 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1182."
    ::= { s450notifications 1182 }

s450UserTrap1183 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1183."
    ::= { s450notifications 1183 }

s450UserTrap1184 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1184."
    ::= { s450notifications 1184 }

s450UserTrap1185 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1185."
    ::= { s450notifications 1185 }

s450UserTrap1186 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1186."
    ::= { s450notifications 1186 }

s450UserTrap1187 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1187."
    ::= { s450notifications 1187 }

s450UserTrap1188 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1188."
    ::= { s450notifications 1188 }

s450UserTrap1189 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1189."
    ::= { s450notifications 1189 }

s450UserTrap1190 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1190."
    ::= { s450notifications 1190 }

s450UserTrap1191 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1191."
    ::= { s450notifications 1191 }

s450UserTrap1192 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1192."
    ::= { s450notifications 1192 }

s450UserTrap1193 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1193."
    ::= { s450notifications 1193 }

s450UserTrap1194 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1194."
    ::= { s450notifications 1194 }

s450UserTrap1195 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1195."
    ::= { s450notifications 1195 }

s450UserTrap1196 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1196."
    ::= { s450notifications 1196 }

s450UserTrap1197 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1197."
    ::= { s450notifications 1197 }

s450UserTrap1198 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1198."
    ::= { s450notifications 1198 }

s450UserTrap1199 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1199."
    ::= { s450notifications 1199 }

END
