-- Acksys enterprise MIB
-- This MIB is compatible with SNMP V2c
-- Clean with VIM command: :g/@[GS]ET/d
ACKSYS-MIB DEFINITIONS ::= BEGIN

IMPORTS
	DisplayString, DateAndTime, RowStatus, TruthValue
		FROM SNMPv2-TC

	enterprises, mgmt, IpAddress, Counter32, Gauge32, TimeTicks,
	Integer32, Unsigned32,
	NOTIFICATION-TYPE, OBJECT-TYPE, MODULE-IDENTITY
		FROM SNMPv2-SMI
	;

--Module Identity
acksys MODULE-IDENTITY
	LAST-UPDATED "202110141505Z"
	ORGANIZATION "ACKSYS Communication & Systems"
	CONTACT-INFO "support@acksys.fr"
	DESCRIPTION	 "SNMPv2C Module for ACKSYS Solutions"
	-- MUST BE in reverse chronological order, see RFC2578
	-- newest version
	REVISION "202202181505Z" DESCRIPTION "V3.18.0.1"
	REVISION "202107021113Z" DESCRIPTION "V3.16.0.1"
	-- oldest version
	::= { enterprises 28097 }

-- textual conventions

-- DisplayString is defined in SNMPv2-TC as OCTET STRING SIZE(0..255)

PhysAddress ::=
	OCTET STRING(SIZE (6))
-- This data type is used to model media addresses.  For many
-- types of media, this will be in a binary representation.
-- For example, an ethernet address would be represented as
-- a string of 6 octets.

WifiFlavor ::= INTEGER {
			b-only(1),
			g-only(2),
			mixed-b-g(3),
			a-only(4),
			n-g(10),
			n-bg(11),
			n-a(12),
			ac(16)
		}
NetifName ::= OCTET STRING(SIZE(0..32))
SecurityModes ::= INTEGER {
			none(1)
			,wep(2)
			,wpa-wpa2-psk(3)
			,wpa-wpa2(4)
			,sae-wpa3-psk(5)
			,wpa3(6)
			,owe(7)
		}
CellSecurityProtocol ::= INTEGER {
			none(0) -- SIM IMSI only
			,pap(1)
			,chap(2)
		}
PeapSecurityProtocol ::= INTEGER {
			peap-pap(1)
			,peap-chap(2)
			,peap-mschap(3)
			,peap-mschapv2(4)
		}
WpaVersions ::= INTEGER { wpa(1), wpa2(2) , wpa-wpa2-mixed(3), wpa3(4), wpa2-wpa3-mixed(5) }
CipherTypes ::= INTEGER { tkip(1), aes(2) , aestkip(3) }
WepKeys ::= OCTET STRING (SIZE (0..26))
-- reasonable signal level values for WiFi
WifiLevel ::= INTEGER (-100..0)
DisableEnable ::= INTEGER { disable(1), enable(2) }
TriState ::= INTEGER { default(0), disable(1), enable(2) }
-- general enum for asynchronous OID operation
AsyncSetStatus ::= INTEGER { set-init(0), set-more(1), set-wait(2),
			set-ok(3), set-fail(4) }

BridgeId ::= OCTET STRING (SIZE (8))
PortId ::= OCTET STRING (SIZE (2))

-- Acksys specific MIBs.
network-product OBJECT IDENTIFIER ::= { acksys 1 }
acksysInternals OBJECT IDENTIFIER ::= { acksys 2 }
c-key-management OBJECT IDENTIFIER ::= { acksys 4 }
alarmSettings OBJECT IDENTIFIER ::= { acksys 5 }
powerStatus OBJECT IDENTIFIER ::= { acksys 6 }
networkStatus OBJECT IDENTIFIER ::= { acksys 7 }
networkConfiguration OBJECT IDENTIFIER ::= { acksys 8 }
serviceStatus OBJECT IDENTIFIER ::= { acksys 9 }
serviceConfiguration OBJECT IDENTIFIER ::= { acksys 10 }

wifiInterface OBJECT IDENTIFIER ::= { network-product 1 }
administration OBJECT IDENTIFIER ::= { network-product 2 }
os-stat OBJECT IDENTIFIER ::= { network-product 3 }
productSpecific OBJECT IDENTIFIER ::= { network-product 4 }
lanInterface OBJECT IDENTIFIER ::= {network-product 5}
serialInterface OBJECT IDENTIFIER ::= {network-product 6}

settings OBJECT IDENTIFIER ::= { wifiInterface 1 }
bridge-mode OBJECT IDENTIFIER ::= { wifiInterface 2 }
access-point-mode OBJECT IDENTIFIER ::= { wifiInterface 3}
advancedSettings OBJECT IDENTIFIER ::= { wifiInterface 4 }

bridgeAPFiltering OBJECT IDENTIFIER ::= { bridge-mode 8}

bridgeRoaming OBJECT IDENTIFIER ::= { bridge-mode 9}
bridgeWirelessScan OBJECT IDENTIFIER ::= { bridge-mode 11}
bridgeNAT OBJECT IDENTIFIER ::= { bridge-mode 12}
bridgeNatPortForwarding OBJECT IDENTIFIER ::= { bridgeNAT 11}

bridgeRoamingAdvanced OBJECT IDENTIFIER ::={bridgeRoaming 1}



apClientFiltering OBJECT IDENTIFIER ::= { access-point-mode 4}

securitySettings OBJECT IDENTIFIER ::= { settings 9 }
securityWEP OBJECT IDENTIFIER ::= { securitySettings 2 }
securityWPA-WPA2 OBJECT IDENTIFIER ::= { securitySettings 3}
securityPresharedKey OBJECT IDENTIFIER ::= { securityWPA-WPA2 1}
securityRadius OBJECT IDENTIFIER ::= { securityWPA-WPA2 2} --Obsolete
securityBackupRadius OBJECT IDENTIFIER ::= { securityWPA-WPA2 3} --Obsolete
securityRadiusAP OBJECT IDENTIFIER ::= { securityRadius 6}
securityRadiusBridge OBJECT IDENTIFIER ::= { securityRadius 7}
securityRadiusAPBackup OBJECT IDENTIFIER ::= { securityRadiusAP 6}
wds OBJECT IDENTIFIER ::= { access-point-mode 5}
lanTimeOutSettings OBJECT IDENTIFIER ::= { access-point-mode 8}


longDistanceSettings OBJECT IDENTIFIER ::= { advancedSettings 1}

wlg-aboard OBJECT IDENTIFIER ::= { productSpecific 1 }


alarmSettingsPower1Down OBJECT IDENTIFIER ::= { alarmSettings 2 }
alarmSettingsPower2Down OBJECT IDENTIFIER ::= { alarmSettings 3 }
alarmSettingsLan1Down OBJECT IDENTIFIER ::= { alarmSettings 4 }
alarmSettingsLan2Down OBJECT IDENTIFIER ::= { alarmSettings 5 }
alarmSettingsLan3Down OBJECT IDENTIFIER ::= { alarmSettings 6 }
alarmSettingsLan4Down OBJECT IDENTIFIER ::= { alarmSettings 7 }
alarmSettingsLan5Down OBJECT IDENTIFIER ::= { alarmSettings 8 }
alarmSettingsLan6Down OBJECT IDENTIFIER ::= { alarmSettings 9 }
alarmSettingsLan7Down OBJECT IDENTIFIER ::= { alarmSettings 10 }
alarmSettingsLan8Down OBJECT IDENTIFIER ::= { alarmSettings 11 }
alarmSettingsWLANDown OBJECT IDENTIFIER ::= { alarmSettings 12 }

serialFormat OBJECT IDENTIFIER ::= { serialInterface 2 }
serialSendTriggers OBJECT IDENTIFIER ::= { serialInterface 3 }
serialServiceVirtualCom OBJECT IDENTIFIER ::= { serialInterface 4 }
serialServiceModbusSlave OBJECT IDENTIFIER ::= { serialInterface 5 }
serialServiceModbusMaster OBJECT IDENTIFIER ::= { serialInterface 6 }
serialServiceTcpRawPortServer OBJECT IDENTIFIER ::= { serialInterface 7 }
serialServiceTcpRawPortClient OBJECT IDENTIFIER ::= { serialInterface 8 }
serialServiceUdpRawPortServer OBJECT IDENTIFIER ::= { serialInterface 9 }

serialSendTriggerCharcount OBJECT IDENTIFIER ::= { serialSendTriggers 1 }
serialSendTriggerIdleDelay OBJECT IDENTIFIER ::= { serialSendTriggers 2 }
serialSendTriggerFrameDelay OBJECT IDENTIFIER ::= { serialSendTriggers 3 }

modbusMasterForwardingTable OBJECT IDENTIFIER ::= { serialServiceModbusMaster 3}
modbusMasterForwardingTable-Rule1 OBJECT IDENTIFIER ::= { modbusMasterForwardingTable 1}
modbusMasterForwardingTable-Rule2 OBJECT IDENTIFIER ::= { modbusMasterForwardingTable 2}
modbusMasterForwardingTable-Rule3 OBJECT IDENTIFIER ::= { modbusMasterForwardingTable 3}
modbusMasterForwardingTable-Rule4 OBJECT IDENTIFIER ::= { modbusMasterForwardingTable 4}
modbusMasterForwardingTable-Rule5 OBJECT IDENTIFIER ::= { modbusMasterForwardingTable 5}
modbusMasterForwardingTable-Rule6 OBJECT IDENTIFIER ::= { modbusMasterForwardingTable 6}
modbusMasterForwardingTable-Rule7 OBJECT IDENTIFIER ::= { modbusMasterForwardingTable 7}
modbusMasterForwardingTable-Rule8 OBJECT IDENTIFIER ::= { modbusMasterForwardingTable 8}

tcpRawServerSerialExtraConfig OBJECT IDENTIFIER ::= { serialServiceTcpRawPortServer 1 }

udpRawServerSerialExtraConfig OBJECT IDENTIFIER ::= { serialServiceUdpRawPortServer 1 }

tcpRawClientSerialExtraConfig OBJECT IDENTIFIER ::= { serialServiceTcpRawPortClient 1 }
tcpRawClientRemoteServers OBJECT IDENTIFIER ::= { serialServiceTcpRawPortClient 7 }
tcpRawClientServer1 OBJECT IDENTIFIER ::= { tcpRawClientRemoteServers 1 }
tcpRawClientServer2 OBJECT IDENTIFIER ::= { tcpRawClientRemoteServers 2 }
tcpRawClientServer3 OBJECT IDENTIFIER ::= { tcpRawClientRemoteServers 3 }
tcpRawClientServer4 OBJECT IDENTIFIER ::= { tcpRawClientRemoteServers 4 }
tcpRawClientServer5 OBJECT IDENTIFIER ::= { tcpRawClientRemoteServers 5 }
tcpRawClientServer6 OBJECT IDENTIFIER ::= { tcpRawClientRemoteServers 6 }
tcpRawClientServer7 OBJECT IDENTIFIER ::= { tcpRawClientRemoteServers 7 }
tcpRawClientServer8 OBJECT IDENTIFIER ::= { tcpRawClientRemoteServers 8 }


--acksys group
acksysProductID OBJECT-TYPE
	SYNTAX INTEGER {
		wlg-link(1),
		wlg-aboard-n(2),
		wlg-link-v2(3),
		wlg-aboard-n-v2(4),
		wlg-switch(5),
		wlg-dongle-oem(6),
		wlg-dongle(7),
		msw-aboard(8),
		wlg-xroad-n(9),
		wlg-xroad-s(10),
		wlg-ida-n(11),
		wlg-ida-s(12),
		wlg-xroad-np(13),
		wlg-ida-np(14),
		m340-wc(18),
		wlg-aboard-npi-v3(19),
		wln-aboard(22),
		wln-aboard-n(23),
		wln-aboard-24(24),
		wln-aboard-48(25),
		wln-aboard-72(26),
		wln-aboard-110(27),
		wln-link-oem-rj(28),
		wln-link-oem-ttl(29),
		wln-xroad(30),
		wln-xroad-v2(31),
		wlg-link-v3(32),
		wlg-4lan(33),
		wln-railbox-1(35),
		wln-railbox-1p(36),
		wln-railbox-2(37),
		wln-railbox-2p(38),
		wln-link-oem-ttl-v2(45)
	}
	MAX-ACCESS read-only
	STATUS current
	DESCRIPTION
		"Return the product Id code.
		The m340-wc is also kown as pmxnow0300.
		[FW:E2080.AC.1:5.52.0]
		[FW:E2080.AC.1-Serial:5.10.0]
		[FW:E2148.AC.1:2.8.0.1]
			"
	::= { acksys 3 }

internalUniqueID OBJECT-TYPE
	SYNTAX PhysAddress
	MAX-ACCESS read-only
	STATUS current
	DESCRIPTION
		"Returns a unique product ID for NDM
		[FW:E2148.AC.1:2.8.0.1]"
	::= { acksysInternals 1 }

internalSerial OBJECT-TYPE
	SYNTAX INTEGER
	MAX-ACCESS read-only
	STATUS current
	DESCRIPTION
		"Returns the motherboard serial number
		[FW:E2148.AC.1:2.8.0.1]"
	::= { acksysInternals 2 }

internalWlanChange OBJECT-TYPE
	SYNTAX INTEGER
	MAX-ACCESS read-only
	STATUS current
	DESCRIPTION
		"Last wlan table change pseudotime
		[FW:E2148.AC.1:2.8.0.1]"
	::= { acksysInternals 3 }

internalRadioChange OBJECT-TYPE
	SYNTAX INTEGER
	MAX-ACCESS read-only
	STATUS current
	DESCRIPTION
		"Last radio table change pseudotime
		[FW:E2148.AC.1:2.8.0.1]"
	::= { acksysInternals 4 }

internalSerialTest OBJECT-TYPE
	SYNTAX INTEGER
	MAX-ACCESS read-write
	STATUS current
	DESCRIPTION
		"Start the serial test
		[FW:E2148.AC.1:2.8.0.1]"
	::= { acksysInternals 5 }

internalSerialTestResult OBJECT-TYPE
	SYNTAX INTEGER
	MAX-ACCESS read-only
	STATUS current
	DESCRIPTION
		"Read the serial test result
		[FW:E2148.AC.1:2.8.0.1]"
	::= { acksysInternals 6 }

internalAlarmSwitch OBJECT-TYPE
	SYNTAX INTEGER
	MAX-ACCESS read-write
	STATUS current
	DESCRIPTION
		"Set ou unset the alarm switch
		[FW:E2148.AC.1:3.14.0.1]"
	::= { acksysInternals 7 }

internalDigitalInput OBJECT-TYPE
	SYNTAX INTEGER
	MAX-ACCESS read-only
	STATUS current
	DESCRIPTION
		"Read the digital input
		[FW:E2148.AC.1:2.8.0.1]"
	::= { acksysInternals 8 }

--network-product

--Wireless Interface group
settingInterfaceSsid OBJECT-TYPE
	SYNTAX DisplayString (SIZE (0..33))
	MAX-ACCESS read-write
	STATUS current
	DESCRIPTION
		"SSID (wireless network name)
		[FW:E2080.AC.1:5.52.0]
		"
	::= { settings 1 }

settingInterfaceWifiMode OBJECT-TYPE
    SYNTAX  INTEGER {
                bridge(1),
                access-point(2)
            }
    MAX-ACCESS  read-write
	STATUS  current
    DESCRIPTION
		"Select between MAX-ACCESS POINT and BRIDGE
		[FW:E2080.AC.1:5.52.0]
		"
    ::= { settings 2 }

settingInterfaceChannel OBJECT-TYPE
	SYNTAX  INTEGER
	MAX-ACCESS  read-write
	STATUS  current
	DESCRIPTION
		"A wireless network uses specific channels to handle communication between clients. Some channels in your area may have interference from other electronic devices. Choose the clearest channel to help optimize the performance and coverage of your wireless network.(used in MAX-ACCESS POINT & AD-HOC BRIDGE modes)
		[FW:E2080.AC.1:5.52.0]
		"
    ::= { settings 3 }

settingInterface80211Mode OBJECT-TYPE
	SYNTAX  INTEGER {
			b-only(1),
			g-only(2),
			mixed-b-g(3),
			a-only(4),
			n-g(10),
			n-bg(11),
			n-a(12)
		}
	MAX-ACCESS  read-write
	STATUS  current
	DESCRIPTION
		"Select IEEE 802.11x compatibility mode.
		[FW:E2080.AC.1:5.52.0]
		"
	::= { settings 4 }

settingInterfaceSuper-a-g-Mode OBJECT-TYPE
	SYNTAX  INTEGER {
			disable(1),
			super-g-without-turbo(2),
			super-g-with-static-turbo(3),
			super-g-with-dynamic-turbo(4)

		}
	MAX-ACCESS  read-write
	STATUS  current
	DESCRIPTION
		"This parameter enables the SUPER A/G mode to reach the 108 Mbits/s speed.
		[FW:E2080.AC.1:5.52.0]
		"
	::= { settings 5 }

settingEnableRadio OBJECT-TYPE
    SYNTAX INTEGER {
    			off(1),
			on(2)
		}
    MAX-ACCESS read-write
    STATUS current
    DESCRIPTION
    	"Enable / Disable wifi radio
		[FW:E2080.AC.1:5.52.0]
		"
    ::= { settings 6 }

settingTxPower OBJECT-TYPE
    SYNTAX INTEGER {
    			high(1),
			medium(2),
			low(3)
		}
    MAX-ACCESS read-write
    STATUS current
    DESCRIPTION
    	"Set WIFI tx power
		[FW:E2080.AC.1:5.52.0]
		"
    ::= { settings 7 }

settingRegion OBJECT-TYPE
    SYNTAX INTEGER {
			israel(2),
			usa(4),
			hong-kong(5),
			canada(6),
			australia(7),
			franceoutdoor(10),
			europe(14),
			japan(17),
			singapore(18),
			korea(20),
			mexico(21),
			indonesia(22),
			china(23),
			russia(27),
			brazil(28),
			chile(29),
			thailand(30),
			peru(31)
		}
    MAX-ACCESS read-write
    STATUS current
    DESCRIPTION
    	"Set WIFI regulation domain
		[FW:E2080.AC.1:5.52.0]
		"
    ::= { settings 8 }

settingAntennaChoice OBJECT-TYPE
	SYNTAX INTEGER {
			diversity(1),
			main(2),
			aux(3)
	}
    MAX-ACCESS read-write
    STATUS current
    DESCRIPTION
    	"Set the antenna type
		[FW:E2080.AC.1:5.52.0]
		"
    ::= { settings 10 }

--Setting Transmission rate
settingTransmisionRate OBJECT-TYPE
	SYNTAX INTEGER
    MAX-ACCESS read-write
    STATUS current
    DESCRIPTION
    	"Set the transmission rate in Mbps
		Automatic : -1
		With SuperAG Mode : 108,96,72,48,36,24,18,12
		Without SuperAG mode : 54,48,36,24,18,12,9,6
		802.11b mode : 11,5.5,2,1
		[FW:E2080.AC.1:5.52.0]
		"
    ::= { settings 11 }

--Setting flag udap sans password
settingFlagUdapnopassword OBJECT-TYPE
	SYNTAX INTEGER {
			false(1),
			true(2)
			}
	MAX-ACCESS read-write
	STATUS current
	DESCRIPTION
		"Configure LAN settings without password
		[FW:E2080.AC.1:5.52.0]
		"
	::= { settings 12 }
--Setting filter in subnet
settingFlagFiltersamenet OBJECT-TYPE
	SYNTAX INTEGER {
			disable(1),
			different-subnet-filtre(2),
			custom-subnet-filtre(3)
			}
	MAX-ACCESS read-write
	STATUS current
	DESCRIPTION
		"Isolate subnet filter
		[FW:E2080.AC.1:5.52.0]
		"
	::= { settings 13 }
--Setting economy filter
settingFlagFilterframecosom OBJECT-TYPE
	SYNTAX INTEGER {
			false(1),
			true(2)
			}
	MAX-ACCESS read-write
	STATUS current
	DESCRIPTION
		"Setting economy filter
		[FW:E2080.AC.1:5.52.0]
		"
	::= { settings 14 }

--Setting DFS support
settingDFSsupport OBJECT-TYPE
	SYNTAX INTEGER {
			false(1),
			true(2)
			}
	MAX-ACCESS read-write
	STATUS current
	DESCRIPTION
		"Setting DFS support
		[FW:E2080.AC.1:5.52.0]
		"
	::= { settings 15 }
settingFilterCustomIpAddr OBJECT-TYPE
    SYNTAX  IpAddress
    MAX-ACCESS read-write
    STATUS current
	DESCRIPTION
		"IP address of the custom subnet
		[FW:E2080.AC.1:5.52.0]
	    "
   	::= { settings 16 }
settingFilterCustomSubnetMask OBJECT-TYPE
    SYNTAX  IpAddress
    MAX-ACCESS read-write
   	STATUS current
   	DESCRIPTION
		"Subnet mask of the custom subnet
		[FW:E2080.AC.1:5.52.0]
		"
    	::= { settings 17 }
-- Advanced setting group
enable802-11d OBJECT-TYPE
	SYNTAX DisableEnable
    MAX-ACCESS read-write
    STATUS current
    DESCRIPTION
    	"
		Enable / disable the 802.11d.
		[FW:E2080.AC.1:5.52.0]
		"
    ::= { advancedSettings 2 }

enableIsolateSTA OBJECT-TYPE
	SYNTAX INTEGER {
		disable(1),
		enable(2)
	}
    MAX-ACCESS read-write
    STATUS current
    DESCRIPTION
    	"
		Enable / disable the isolating access point.
		[FW:E2080.AC.1:5.52.0]
		"
    ::= { advancedSettings 3 }

-- long distance settings groups
enableLongDistance OBJECT-TYPE
	SYNTAX DisableEnable
    MAX-ACCESS read-write
    STATUS current
    DESCRIPTION
    	"
		Enable / disable distance parameter.
		[FW:E2080.AC.1:5.52.0]
		"
    ::= { longDistanceSettings 1 }

distanceAntennaMeter OBJECT-TYPE
	SYNTAX INTEGER
    MAX-ACCESS read-write
    STATUS current
    DESCRIPTION
    	"
		Set the distance between antenna in meter.
		[FW:E2080.AC.1:5.52.0]
		"
    ::= { longDistanceSettings 2 }

distanceSlotTime OBJECT-TYPE
	SYNTAX INTEGER
    MAX-ACCESS read-write
    STATUS current
    DESCRIPTION
    	"
		[FW:E2080.AC.1:5.52.0]
		"
    ::= { longDistanceSettings 3 }

distanceAckTimeout OBJECT-TYPE
	SYNTAX INTEGER
    MAX-ACCESS read-write
    STATUS current
    DESCRIPTION
    	"
		[FW:E2080.AC.1:5.52.0]
		"
    ::= { longDistanceSettings 4 }

distanceCtsTimeout OBJECT-TYPE
	SYNTAX INTEGER
    MAX-ACCESS read-write
    STATUS current
    DESCRIPTION
    	"
		[FW:E2080.AC.1:5.52.0]
		"
    ::= { longDistanceSettings 5 }

--Setting security group
securityMode OBJECT-TYPE
	SYNTAX SecurityModes
    MAX-ACCESS read-write
    STATUS current
    DESCRIPTION
    	"Set the security mode
		[FW:E2080.AC.1:5.52.0]"
    ::= { securitySettings 1 }

--WEP group
securityModeWepKeyLen OBJECT-TYPE
    SYNTAX INTEGER
    MAX-ACCESS read-write
    STATUS current
    DESCRIPTION
		"Set the WEP key len (64 bits or 128 bits)
		[FW:E2080.AC.1:5.52.0]"
    ::= { securityWEP 1 }

securityModeWepKey-1 OBJECT-TYPE
    SYNTAX WepKeys
    MAX-ACCESS read-write
    STATUS current
    DESCRIPTION
		"WEP key 1 in hexadecimal format
		[FW:E2080.AC.1:5.52.0]"
    ::= { securityWEP 2 }

securityModeWepKey-2 OBJECT-TYPE
    SYNTAX WepKeys
    MAX-ACCESS read-write
    STATUS current
    DESCRIPTION
		"WEP key 2 in hexadecimal format
		[FW:E2080.AC.1:5.52.0]"
    ::= { securityWEP 3 }

securityModeWepKey-3 OBJECT-TYPE
    SYNTAX WepKeys
    MAX-ACCESS read-write
    STATUS current
    DESCRIPTION
		"WEP key 3 in hexadecimal format
		[FW:E2080.AC.1:5.52.0]"
    ::= { securityWEP 4 }

securityModeWepKey-4 OBJECT-TYPE
    SYNTAX WepKeys
    MAX-ACCESS read-write
    STATUS current
    DESCRIPTION
		"WEP key 4 in hexadecimal format
		[FW:E2080.AC.1:5.52.0]"
    ::= { securityWEP 5 }

securityModeDefaultWepKey OBJECT-TYPE
    SYNTAX INTEGER
    MAX-ACCESS read-write
    STATUS current
    DESCRIPTION
		"Set the wep key used
		[FW:E2080.AC.1:5.52.0]"
    ::= { securityWEP 6 }

securityModeWepAuthentication OBJECT-TYPE
    SYNTAX INTEGER {
		open(1),
		shared(2)
	}
    MAX-ACCESS read-write
    STATUS current
    DESCRIPTION
		"Set WEP Authentication
		[FW:E2080.AC.1:5.52.0]"
    ::= { securityWEP 7 }

--WPA/WPA2-PSK group

securityModeWpaMode OBJECT-TYPE
    SYNTAX INTEGER {
		wpa(1),
		wpa2(2),
		wpa3(3)
	}
    MAX-ACCESS read-write
    STATUS current
    DESCRIPTION
		"Select the wpa mode
		[FW:E2080.AC.1:5.52.0]"
    ::= { securityWPA-WPA2 4 }

securityModeWpaCipherType OBJECT-TYPE
    SYNTAX CipherTypes
    MAX-ACCESS read-write
    STATUS current
    DESCRIPTION
		"select the cipher type
		[FW:E2080.AC.1:5.52.0]"
    ::= { securityWPA-WPA2 5 }

securityModeWpaKeyUpdateInterval OBJECT-TYPE
    SYNTAX INTEGER
    MAX-ACCESS read-write
    STATUS current
    DESCRIPTION
		"Set the group key interval
		[FW:E2080.AC.1:5.52.0]"
    ::= { securityWPA-WPA2 6 }

--Pre-shared key group
securityModeWpaPresharedKey OBJECT-TYPE
    SYNTAX OCTET STRING (SIZE (8..64))
    MAX-ACCESS read-write
    STATUS current
    DESCRIPTION
		"Set the group key interval
		[FW:E2080.AC.1:5.52.0]"
    ::= { securityPresharedKey 1 }

-- radius AP
securityModeWPARadiusAPAuthenticationTimeout OBJECT-TYPE
	SYNTAX INTEGER
    MAX-ACCESS read-write
    STATUS current
    DESCRIPTION
		"Set the group key interval
		[FW:E2080.AC.1:5.52.0]"
    ::= { securityRadiusAP 1 }

securityModeWPARadiusAPIP OBJECT-TYPE
	SYNTAX  IpAddress
    MAX-ACCESS read-write
    STATUS current
    DESCRIPTION
		"Set the group key interval
		[FW:E2080.AC.1:5.52.0]"
    ::= { securityRadiusAP 2 }

securityModeWPARadiusAPPort OBJECT-TYPE
	SYNTAX  INTEGER
    MAX-ACCESS read-write
    STATUS current
    DESCRIPTION
		"Set the group key interval
		[FW:E2080.AC.1:5.52.0]"
    ::= { securityRadiusAP 3 }

securityModeWPARadiusAPSecret OBJECT-TYPE
	SYNTAX OCTET STRING (SIZE (1..64))
    MAX-ACCESS read-write
    STATUS current
    DESCRIPTION
		"Set the group key interval
		[FW:E2080.AC.1:5.52.0]"
    ::= { securityRadiusAP 4 }

securityModeWPARadiusAPMacAddressAuthentication OBJECT-TYPE
	SYNTAX DisableEnable
    MAX-ACCESS read-write
    STATUS current
    DESCRIPTION
		"Set the group key interval
		[FW:E2080.AC.1:5.52.0]"
    ::= { securityRadiusAP 5 }
--Obsolete OIDs
securityModeWPARadiusAuthenticationTimeout OBJECT-TYPE
	SYNTAX INTEGER
    MAX-ACCESS read-write
    STATUS obsolete
    DESCRIPTION
		"Set the group key interval
		[FW:E2080.AC.1:5.52.0]"
    ::= { securityRadius 1 }

securityModeWPARadiusIP OBJECT-TYPE
	SYNTAX  IpAddress
    MAX-ACCESS read-write
    STATUS obsolete
    DESCRIPTION
		"Set the group key interval
		[FW:E2080.AC.1:5.52.0]"
    ::= { securityRadius 2 }

securityModeWPARadiusPort OBJECT-TYPE
	SYNTAX  INTEGER
    MAX-ACCESS read-write
    STATUS obsolete
    DESCRIPTION
		"Set the group key interval
		[FW:E2080.AC.1:5.52.0]"
    ::= { securityRadius 3 }

securityModeWPARadiusSecret OBJECT-TYPE
	SYNTAX OCTET STRING (SIZE (1..64))
    MAX-ACCESS read-write
    STATUS obsolete
    DESCRIPTION
		"Set the group key interval
		[FW:E2080.AC.1:5.52.0]"
    ::= { securityRadius 4 }

securityModeWPARadiusMacAddressAuthentication OBJECT-TYPE
	SYNTAX DisableEnable
    MAX-ACCESS read-write
    STATUS obsolete
    DESCRIPTION
		"Set the group key interval
		[FW:E2080.AC.1:5.52.0]"
    ::= { securityRadius 5 }
--End of Obsolete OIDs

-- backup radius
securityModeWPABackupRadiusAPIP OBJECT-TYPE
	SYNTAX  IpAddress
    MAX-ACCESS read-write
    STATUS current
    DESCRIPTION
		"Set the group key interval
		[FW:E2080.AC.1:5.52.0]"
    ::= { securityRadiusAPBackup 1 }

securityModeWPARadiusBackupAPPort OBJECT-TYPE
	SYNTAX  INTEGER
    MAX-ACCESS read-write
    STATUS current
    DESCRIPTION
		"Set the group key interval
		[FW:E2080.AC.1:5.52.0]"
    ::= { securityRadiusAPBackup 2 }

securityModeWPARadiusBackupAPSecret OBJECT-TYPE
	SYNTAX OCTET STRING (SIZE (1..64))
    MAX-ACCESS read-write
    STATUS current
    DESCRIPTION
		"Set the group key interval
		[FW:E2080.AC.1:5.52.0]"
    ::= { securityRadiusAPBackup 3 }

securityModeWPABackupRadiusAPMacAddressAuthentication OBJECT-TYPE
	SYNTAX DisableEnable
    MAX-ACCESS read-write
    STATUS current
    DESCRIPTION
		"Set the group key interval
		[FW:E2080.AC.1:5.52.0]"
    ::= { securityRadiusAPBackup 4 }

--Obsolete OIDs
securityModeWPABackupRadiusIP OBJECT-TYPE
	SYNTAX  IpAddress
    MAX-ACCESS read-write
    STATUS obsolete
    DESCRIPTION
		"Set the group key interval
		[FW:E2080.AC.1:5.52.0]"
    ::= { securityBackupRadius 1 }

securityModeWPARadiusBackupPort OBJECT-TYPE
	SYNTAX  INTEGER
    MAX-ACCESS read-write
    STATUS obsolete
    DESCRIPTION
		"Set the group key interval
		[FW:E2080.AC.1:5.52.0]"
    ::= { securityBackupRadius 2 }

securityModeWPARadiusBackupSecret OBJECT-TYPE
	SYNTAX OCTET STRING (SIZE (1..64))
    MAX-ACCESS read-write
    STATUS obsolete
    DESCRIPTION
		"Set the group key interval
		[FW:E2080.AC.1:5.52.0]"
    ::= { securityBackupRadius 3 }

securityModeWPABackupRadiusMacAddressAuthentication OBJECT-TYPE
	SYNTAX DisableEnable
    MAX-ACCESS read-write
    STATUS obsolete
    DESCRIPTION
		"Set the group key interval
		[FW:E2080.AC.1:5.52.0]"
    ::= { securityBackupRadius 4 }
--End of Obsolete OIDs

-- radius Bridge
securityModeWPARadiusLogin OBJECT-TYPE
	SYNTAX OCTET STRING (SIZE (1..64))
    MAX-ACCESS read-write
    STATUS current
    DESCRIPTION
		"Set the group key interval
		[FW:E2080.AC.1:5.52.0]"
    ::= { securityRadiusBridge 1 }

securityModeWPARadiusPassword OBJECT-TYPE
	SYNTAX OCTET STRING (SIZE (1..64))
    MAX-ACCESS read-write
    STATUS current
    DESCRIPTION
		"Set the group key interval
		[FW:E2080.AC.1:5.52.0]"
    ::= { securityRadiusBridge 2 }


--Access point group
apClientTable OBJECT-TYPE
    SYNTAX  SEQUENCE OF ApClientEntry
    MAX-ACCESS  not-accessible
    STATUS  current
    DESCRIPTION
		"Significant only in MAX-ACCESS POINT mode. This table shows information about connected clients.
		[FW:E2080.AC.1:5.52.0]"
    ::= { access-point-mode 1 }

apAutomaticChannel OBJECT-TYPE
    SYNTAX INTEGER {
			off(1),
			on(2)
		}
    MAX-ACCESS read-write
    STATUS current
    DESCRIPTION
    	"Enable / disable the automatic channel select
		[FW:E2080.AC.1:5.52.0]
	"
    ::= { access-point-mode 2}

apClientCount OBJECT-TYPE
    SYNTAX INTEGER
    MAX-ACCESS read-only
    STATUS current
    DESCRIPTION
    	"count the number of entries in ApClientEntry
		[FW:E2080.AC.1:5.52.0]
		"
    ::= { access-point-mode 3}

apClientEntry OBJECT-TYPE
    SYNTAX  ApClientEntry
    MAX-ACCESS  not-accessible
    STATUS  current
    DESCRIPTION
		"Shows information about the connected client.
		[FW:E2080.AC.1:5.52.0]
		"
    INDEX   { clientMacAddr }
    ::= { apClientTable 1 }

ApClientEntry ::=
    SEQUENCE {
        clientMacAddr
            PhysAddress,
        client80211Mode
			INTEGER,
		clientTxRate
			INTEGER ,
		clientRssiPercent
			Gauge32
	}

clientMacAddr OBJECT-TYPE
    SYNTAX PhysAddress
    MAX-ACCESS read-only
    STATUS current
    DESCRIPTION
		"MAC address of the client connected to the AP.
		[FW:E2080.AC.1:5.52.0]"
    ::= { apClientEntry 1 }

client80211Mode OBJECT-TYPE
    SYNTAX INTEGER {
		b-only(1),
		g-only(2),
		mixed-b-g(3),
		a-only(4)
    }
    MAX-ACCESS read-only
    STATUS current
    DESCRIPTION
		"Show client's IEEE 802.11x compatibility mode.
		[FW:E2080.AC.1:5.52.0]"
    ::= { apClientEntry 2 }

clientTxRate OBJECT-TYPE
    SYNTAX INTEGER
    MAX-ACCESS read-only
    STATUS current
    DESCRIPTION
		"Client's communication speed in bits per second
		[FW:E2080.AC.1:5.52.0]"
    ::= { apClientEntry 3 }

clientRssiPercent OBJECT-TYPE
    SYNTAX Gauge32
    MAX-ACCESS read-only
    STATUS current
    DESCRIPTION
		"Client's RSSI (percent)
		[FW:E2080.AC.1:5.52.0]"
    ::= { apClientEntry 4}

settingSSIDVisibility OBJECT-TYPE
	SYNTAX INTEGER {
			visible(2),
			invisible(1)
	}
    MAX-ACCESS read-write
    STATUS current
    DESCRIPTION
    	"Enable or Disable SSID Visibility
		[FW:E2080.AC.1:5.52.0]
		"
    ::= { access-point-mode 6}

enableSTP OBJECT-TYPE
	SYNTAX DisableEnable
    MAX-ACCESS read-write
    STATUS current
    DESCRIPTION
    	"Enable / disable STP protocol.
		[FW:E2080.AC.1:5.52.0]
		"
    ::= { access-point-mode 7 }

enableLanTimeout OBJECT-TYPE
	SYNTAX DisableEnable
    MAX-ACCESS read-write
    STATUS current
    DESCRIPTION
    	" Enable / disable LAN timeout.
		ACCESS POINT can be configured to auto-disconnect the radio when the LAN is disconnected from the equipment.
		[FW:E2080.AC.1:5.52.0]
	"
    ::= { lanTimeOutSettings 1 }

lanTimeoutIPSurvey OBJECT-TYPE
	SYNTAX INTEGER
    MAX-ACCESS read-write
    STATUS current
    DESCRIPTION
		"
		Define the IP address where the probe was be sent.
		[FW:E2080.AC.1:5.52.0]
	"
    ::= { lanTimeOutSettings 2 }

lanTimeoutMaxProbe OBJECT-TYPE
	SYNTAX INTEGER
    MAX-ACCESS read-write
    STATUS current
    DESCRIPTION
		"
		Define the number of probe without response necessairy to disconnect the radio.
		[FW:E2080.AC.1:5.52.0]
		"
    ::= { lanTimeOutSettings 3 }

lanTimeoutProbeTimeout OBJECT-TYPE
	SYNTAX INTEGER
    MAX-ACCESS read-write
    STATUS current
    DESCRIPTION
		"
		Define the probe response waiting time in seconds.
		[FW:E2080.AC.1:5.52.0]
		"
    ::= { lanTimeOutSettings 4 }

lanTimeoutProbeInterval OBJECT-TYPE
	SYNTAX INTEGER
    MAX-ACCESS read-write
    STATUS current
    DESCRIPTION
		"
		Define the times in seconds between each probes.
		[FW:E2080.AC.1:5.52.0]
		"
    ::= { lanTimeOutSettings 5 }


--======================
--AP Filtering

apClientFilteringEnable OBJECT-TYPE
	SYNTAX  INTEGER {
			off(1),
          on(2)
		}
	MAX-ACCESS  read-write
	STATUS  current
	DESCRIPTION "Enable / Disable Client Filtering.
		[FW:E2080.AC.1:5.52.0]
		"
	::= { apClientFiltering 1 }

apClientFilteringMode OBJECT-TYPE
	SYNTAX  INTEGER {
			allow(1),
			deny(2)
		}
	MAX-ACCESS  read-write
	STATUS  current
	DESCRIPTION "Select Client Filtering Mode (allow/Deny)
		[FW:E2080.AC.1:5.52.0]
		"
	::= { apClientFiltering 2 }

apClientWirelessFiltering OBJECT-TYPE
	SYNTAX DisableEnable
	MAX-ACCESS  read-write
	STATUS  current
	DESCRIPTION "Enable or disable Wireless client filtering
		[FW:E2080.AC.1:5.52.0]
		"
	::= { apClientFiltering 3 }

apClientWiredFiltering OBJECT-TYPE
	SYNTAX DisableEnable
	MAX-ACCESS  read-write
	STATUS  current
	DESCRIPTION "Enable or disable Wireless client filtering
		[FW:E2080.AC.1:5.52.0]
		"
	::= { apClientFiltering 4 }

apClientFilteringMACAddress OBJECT-TYPE
	SYNTAX  PhysAddress
	MAX-ACCESS  read-write
	STATUS  current
	DESCRIPTION "
		MAC address field
		[FW:E2080.AC.1:5.52.0]
		"
	::= { apClientFiltering 5 }

apClientFilteringName OBJECT-TYPE
	SYNTAX OCTET STRING (SIZE (1..64))
  	MAX-ACCESS read-write
    STATUS current
    DESCRIPTION
        "Name Field
		[FW:E2080.AC.1:5.52.0]
		"
  ::= { apClientFiltering 6}

apClientFilteringSave OBJECT-TYPE
	SYNTAX  INTEGER
	MAX-ACCESS  read-write
	STATUS  current
	DESCRIPTION "write 1 to save the rule
		[FW:E2080.AC.1:5.52.0]
		"
	::= { apClientFiltering 7 }

apClientFilteringDelete OBJECT-TYPE
	SYNTAX  INTEGER
	MAX-ACCESS  read-write
	STATUS  current
	DESCRIPTION "when writed, delete the rule which is indexed by the written value
		[FW:E2080.AC.1:5.52.0]
		"
	::= { apClientFiltering 8 }

apClientFilteringEnableRule OBJECT-TYPE
	SYNTAX  INTEGER
	MAX-ACCESS  read-write
	STATUS  current
	DESCRIPTION "when writed, enable the rule which is indexed by the written value
		[FW:E2080.AC.1:5.52.0]
		"
	::= { apClientFiltering 9 }

apClientFilteringDisableRule OBJECT-TYPE
	SYNTAX  INTEGER
	MAX-ACCESS  read-write
	STATUS  current
	DESCRIPTION "when writed, disable the rule which is indexed by the written value
		[FW:E2080.AC.1:5.52.0]
		"
	::= { apClientFiltering 10 }

apClientFilteringTable OBJECT-TYPE
    SYNTAX  SEQUENCE OF ApClientFilteringEntry
    MAX-ACCESS  not-accessible
    STATUS  current
    DESCRIPTION
		"Significant only in MAX-ACCESS POINT mode. This table shows information AP bridge filtering rules list.
		[FW:E2080.AC.1:5.52.0]
		"
    ::= { apClientFiltering 11 }


apClientFilteringEntry OBJECT-TYPE
    SYNTAX  ApClientFilteringEntry
    MAX-ACCESS  not-accessible
    STATUS  current
   DESCRIPTION
        "Shows information of the rule.
		[FW:E2080.AC.1:5.52.0]
		"
    INDEX   { apClientFilteringListId }
    ::= { apClientFilteringTable 1 }

ApClientFilteringEntry ::=
    SEQUENCE {
		apClientFilteringListId
			INTEGER,
		apClientFilteringListName
			OCTET STRING,
        apClientFilteringListMAC
            PhysAddress,
		apClientFilteringListEnable
			INTEGER
	}

apClientFilteringListId OBJECT-TYPE
    SYNTAX INTEGER
    MAX-ACCESS read-only
    STATUS current
    DESCRIPTION
		"Rule index.
		[FW:E2080.AC.1:5.52.0]"
    ::= { apClientFilteringEntry 1 }

apClientFilteringListMAC OBJECT-TYPE
    SYNTAX PhysAddress
    MAX-ACCESS read-only
    STATUS current
    DESCRIPTION
		"MAC address of the client.
		[FW:E2080.AC.1:5.52.0]"
    ::= { apClientFilteringEntry 3 }

apClientFilteringListName OBJECT-TYPE
    SYNTAX OCTET STRING (SIZE (1..64))
    MAX-ACCESS read-only
    STATUS current
    DESCRIPTION
		"Show rule's name
		[FW:E2080.AC.1:5.52.0]"
    ::= { apClientFilteringEntry 2 }

apClientFilteringListEnable OBJECT-TYPE
	SYNTAX DisableEnable
	MAX-ACCESS  read-only
	STATUS  current
	DESCRIPTION "Show if the rule is enabled or not.
		[FW:E2080.AC.1:5.52.0]"
	::= { apClientFilteringEntry 4 }



--End AP Filtering
--======================

--======================
--WDS
apWDSEnable OBJECT-TYPE
	SYNTAX DisableEnable
	MAX-ACCESS  read-write
	STATUS  current
	DESCRIPTION "Enable or Disable WDS.
		[FW:E2080.AC.1:5.52.0]
		"
	::= { wds 1 }

apWDSEnableSTP OBJECT-TYPE
	SYNTAX DisableEnable
	MAX-ACCESS  read-write
	STATUS  current
	DESCRIPTION "Enable or Disable STP when WDS is on
		[FW:E2080.AC.1:5.52.0]"
	::= { wds 2 }

apWDSMAC1 OBJECT-TYPE
	SYNTAX  PhysAddress
	MAX-ACCESS  read-write
	STATUS  current
	DESCRIPTION "
		First AP mac address
		[FW:E2080.AC.1:5.52.0]
		"
	::= { wds 3 }

apWDSMAC2 OBJECT-TYPE
	SYNTAX  PhysAddress
	MAX-ACCESS  read-write
	STATUS  current
	DESCRIPTION "
		Second AP mac address
		[FW:E2080.AC.1:5.52.0]
		"
	::= { wds 4 }

apWDSMAC3 OBJECT-TYPE
	SYNTAX  PhysAddress
	MAX-ACCESS  read-write
	STATUS  current
	DESCRIPTION "
		Third AP mac address
		[FW:E2080.AC.1:5.52.0]
		"
	::= { wds 5 }

apWDSMAC4 OBJECT-TYPE
	SYNTAX  PhysAddress
	MAX-ACCESS  read-write
	STATUS  current
	DESCRIPTION "
		Fourth AP mac address
		[FW:E2080.AC.1:5.52.0]
		"
	::= { wds 6 }

apWDSMAC5 OBJECT-TYPE
	SYNTAX  PhysAddress
	MAX-ACCESS  read-write
	STATUS  current
	DESCRIPTION "
		Fifth AP mac address
		[FW:E2080.AC.1:5.52.0]
		"
	::= { wds 7 }

apWDSMAC6 OBJECT-TYPE
	SYNTAX  PhysAddress
	MAX-ACCESS  read-write
	STATUS  current
	DESCRIPTION "
		Sixth AP mac address
		[FW:E2080.AC.1:5.52.0]
		"
	::= { wds 8 }

--bridge group
bridge-modeLinkStatus OBJECT-TYPE
	SYNTAX  INTEGER {
			up(1),       -- ready to pass packets
            down(2)
		}
	MAX-ACCESS  read-only
	STATUS  current
	DESCRIPTION "MAX-ACCESS POINT's connection status.
		[FW:E2080.AC.1:5.52.0]
		"
	::= { bridge-mode 1 }

bridge-modeMacAP OBJECT-TYPE
	SYNTAX  PhysAddress
	MAX-ACCESS  read-only
	STATUS  current
	DESCRIPTION "
		MAX-ACCESS POINT's MAC ADDRESS we are connected with.
		[FW:E2080.AC.1:5.52.0]
	"
	::= { bridge-mode 2 }

bridge-modeRSSI OBJECT-TYPE
	SYNTAX  Gauge32
	MAX-ACCESS  read-only
	STATUS  current
	DESCRIPTION "
		MAX-ACCESS POINT's connection RSSI.
		[FW:E2080.AC.1:5.52.0]
	 "
	::= { bridge-mode 3 }

bridge-modeRSSIdBm OBJECT-TYPE
	SYNTAX  Gauge32
	MAX-ACCESS  read-only
	STATUS  current
	DESCRIPTION "
		Connection's RSSI in dBm.
		[FW:E2080.AC.1:5.52.0]
	"
	::= { bridge-mode 4 }

bridge-modeRSSIPercent OBJECT-TYPE
	SYNTAX  Gauge32
	MAX-ACCESS  read-only
	STATUS  current
	DESCRIPTION "
		Connection's RSSI in percent.
		[FW:E2080.AC.1:5.52.0]
	"
	::= { bridge-mode 5}

bridge-modeCurrentTxRate OBJECT-TYPE
	SYNTAX  INTEGER
	MAX-ACCESS  read-only
	STATUS  current
	DESCRIPTION "
		Current communication speed in bits per second.
		[FW:E2080.AC.1:5.52.0]
	"
	::= { bridge-mode 6}

bridge-WirelessMode OBJECT-TYPE
    SYNTAX INTEGER {
			infrastructure(1),
			ad-hoc(2)
		}
    MAX-ACCESS read-write
    STATUS current
    DESCRIPTION
    	"Select the Wireless mode. Infrastructure mode require an access point.
		[FW:E2080.AC.1:5.52.0]
	"
    ::= { bridge-mode 7}

--*********************

--********************
-- bridge

bridgeAPFilteringEnable OBJECT-TYPE
	SYNTAX  INTEGER {
			off(1),
            on(2)
		}
	MAX-ACCESS  read-write
	STATUS  current
	DESCRIPTION "Enable or Disable AP Filtering.
		[FW:E2080.AC.1:5.52.0]
		"
	::= { bridgeAPFiltering 1 }

bridgeAPFilteringMode OBJECT-TYPE
	SYNTAX  INTEGER {
			allow(1),
    	    deny(2)
		}
	MAX-ACCESS  read-write
	STATUS  current
	DESCRIPTION "Select AP Filtering Mode (allow/Deny)
		[FW:E2080.AC.1:5.52.0]
		"
	::= { bridgeAPFiltering 2 }

bridgeAPFilteringMACAddress OBJECT-TYPE
	SYNTAX  PhysAddress
	MAX-ACCESS  read-write
	STATUS  current
	DESCRIPTION "
		MAC address field
		[FW:E2080.AC.1:5.52.0]
		"
	::= { bridgeAPFiltering 3 }

bridgeAPFilteringName OBJECT-TYPE
	SYNTAX OCTET STRING (SIZE (1..64))
	MAX-ACCESS read-write
    STATUS current
    DESCRIPTION
            "Name Field
			[FW:E2080.AC.1:5.52.0]
			"
    ::= { bridgeAPFiltering 4 }

bridgeAPFilteringSave OBJECT-TYPE
	SYNTAX  INTEGER
	MAX-ACCESS  read-write
	STATUS  current
	DESCRIPTION "write 1 to save the rule
		[FW:E2080.AC.1:5.52.0]
		"
	::= { bridgeAPFiltering 5 }

bridgeAPFilteringDelete OBJECT-TYPE
	SYNTAX  INTEGER
	MAX-ACCESS  read-write
	STATUS  current
	DESCRIPTION "when writed, delete the rule which is indexed by the written value
		[FW:E2080.AC.1:5.52.0]
		"
	::= { bridgeAPFiltering 6 }

bridgeAPFilteringEnableRule OBJECT-TYPE
	SYNTAX  INTEGER
	MAX-ACCESS  read-write
	STATUS  current
	DESCRIPTION "when writed, enable the rule which is indexed by the written value
		[FW:E2080.AC.1:5.52.0]
		"
	::= { bridgeAPFiltering 7 }

bridgeAPFilteringDisableRule OBJECT-TYPE
	SYNTAX  INTEGER
	MAX-ACCESS  read-write
	STATUS  current
	DESCRIPTION "when writed, disable the rule which is indexed by the written value
		[FW:E2080.AC.1:5.52.0]
		"
	::= { bridgeAPFiltering 8 }


bridgeAPFilteringTable OBJECT-TYPE
    SYNTAX  SEQUENCE OF BridgeAPFilteringEntry
    MAX-ACCESS  not-accessible
    STATUS  current
    DESCRIPTION
		"Significant only in MAX-ACCESS POINT mode. This table shows information bridge AP filtering rules list.
		[FW:E2080.AC.1:5.52.0]"
    ::= { bridgeAPFiltering 9 }

bridgeAPFilteringEntry OBJECT-TYPE
    SYNTAX  BridgeAPFilteringEntry
    MAX-ACCESS  not-accessible
    STATUS  current
    DESCRIPTION
		"Shows information of the rule.
		[FW:E2080.AC.1:5.52.0]
		"
    INDEX   { bridgeAPFilteringListId }
    ::= { bridgeAPFilteringTable 1 }

BridgeAPFilteringEntry ::=
    SEQUENCE {
		bridgeAPFilteringListId
			INTEGER,
	    bridgeAPFilteringListName
			OCTET STRING,
        bridgeAPFilteringListMAC
            PhysAddress,
		bridgeAPFilteringListEnable
			INTEGER
	}

bridgeAPFilteringListId OBJECT-TYPE
    SYNTAX INTEGER
    MAX-ACCESS read-only
    STATUS current
    DESCRIPTION
		"Rule index.
		[FW:E2080.AC.1:5.52.0]"
    ::= { bridgeAPFilteringEntry 1 }

bridgeAPFilteringListMAC OBJECT-TYPE
   SYNTAX PhysAddress
    MAX-ACCESS read-only
    STATUS current
    DESCRIPTION
		"MAC address of the client.
		[FW:E2080.AC.1:5.52.0]"
    ::= { bridgeAPFilteringEntry 3 }

bridgeAPFilteringListName OBJECT-TYPE
    SYNTAX OCTET STRING (SIZE (1..64))
    MAX-ACCESS read-only
    STATUS current
    DESCRIPTION
		"Show rule's name
		[FW:E2080.AC.1:5.52.0]"
    ::= { bridgeAPFilteringEntry 2 }

bridgeAPFilteringListEnable OBJECT-TYPE
	SYNTAX DisableEnable
	MAX-ACCESS  read-only
	STATUS  current
	DESCRIPTION "
		Show if a rule is enabled or not.
		[FW:E2080.AC.1:5.52.0]"
	::= { bridgeAPFilteringEntry 4 }

bridgeChannelList OBJECT-TYPE
	SYNTAX OCTET STRING (SIZE (1..40))
	MAX-ACCESS  read-write
	STATUS  current
	DESCRIPTION "A wireless network uses specific channels in the 2.4GHz or
		5GHz wireless spectrum to handle communication between clients.
		Some channels in your area may have interference from other electronic
		devices. Your wireless bridge will use the channel that is used by the
		access point it will associate with. But you can select here your
		channel preference to help optimize the performance and coverage of
		your wireless network. If you used the roaming, Acksys recommend to
		used only one channel for better bandwith.
		[FW:E2080.AC.1:5.52.0]
		"
	::= { bridge-mode 10 }

--roaming setting
bridgeRoamingEnable OBJECT-TYPE
	SYNTAX DisableEnable
	MAX-ACCESS read-write
	STATUS  current
	DESCRIPTION " Roaming enables WiFi clients to roam among AP when WiFi RSSI
		of the current AP becomes weak. This radio button enables/disables the
		roaming capabilities of the bridge.
		[FW:E2080.AC.1:5.52.0]
		"
	::={bridgeRoaming 2}

bridgeRoamingRSSIThreshold-dBm OBJECT-TYPE
	SYNTAX INTEGER
	MAX-ACCESS read-write
	STATUS  current
	DESCRIPTION "Allows to configure the RSSI roaming threshold in dBm from
		which the roaming algorithm (to find a better AP) will start. AP
		changing will only be effective if the current RSSI is lower than that
		threshold, and if a new AP with a better RSSI has been detected.
		[FW:E2080.AC.1:5.52.0]
		"
	::= {bridgeRoaming 3}

bridgeRoamingRSSIThreshold-percent OBJECT-TYPE
	SYNTAX INTEGER
	MAX-ACCESS read-write
	STATUS  current
	DESCRIPTION " Allows to configure the RSSI roaming threshold in percent from
		which the roaming algorithm (to find a better AP) will start. AP changing
		will only be effective if the current RSSI is lower than that threshold,
		and if a new AP with a better RSSI has been detected.
		[FW:E2080.AC.1:5.52.0]
		"
	::= {bridgeRoaming 4}

bridgeRoamingAdvancedScanThreshold-dbm OBJECT-TYPE
	SYNTAX INTEGER
	MAX-ACCESS	read-write
	STATUS  current
	DESCRIPTION "Allows to configure the RSSI scan threshold in dBm from
		which the access point active scan will start. The access point active
		scan process looking on each valid channel the access point where it
		will be possible to roam.
		[FW:E2080.AC.1:5.52.0]
		"
	::= {bridgeRoamingAdvanced 1}

bridgeRoamingAdvancedScanThreshold-percent OBJECT-TYPE
	SYNTAX INTEGER
	MAX-ACCESS	read-write
	STATUS  current
	DESCRIPTION "Allows to configure the RSSI scan threshold in percent from
		which the access point active scan will start. The access point active
		scan process looking on each valid channel the access point where it
		will be possible to roam.
		[FW:E2080.AC.1:5.52.0]
		"
	::= {bridgeRoamingAdvanced 2}

bridgeRoamingAdvancedScanPeriod OBJECT-TYPE
	SYNTAX INTEGER
	MAX-ACCESS	read-write
	STATUS  current
	DESCRIPTION "Allow to configure the time between two scan.
		Reduce this time increase the Access Point discover, but decrease the
		bandwith if you used more one channel.
		[FW:E2080.AC.1:5.52.0]
		"
	::= {bridgeRoamingAdvanced 3}

bridgeRoamingAdvancedScanDuration OBJECT-TYPE
	SYNTAX INTEGER
	MAX-ACCESS	read-write
	STATUS  current
	DESCRIPTION "Allow to configure the duration while the bridge waiting the Access Point answer.
		Reduce this duration increase the Bandwith when you used more one channel, but decrase the Access Point discover.
		[FW:E2080.AC.1:5.52.0]
		"
	::= {bridgeRoamingAdvanced 4}

bridgeRoamingAdvancedAPLossDetection OBJECT-TYPE
	SYNTAX INTEGER
	MAX-ACCESS	read-write
	STATUS  current
	DESCRIPTION "If nothing is received from the AP during a certain amount of time, it will be considered unreachable.
		This amount of time is computed as:
		'AP timeout' = 'AP loss detection' x 'beacon interval'.
		The recommended value for 'AP loss detection' is 5.
		The recommended value for 'Beacon interval' (which should be configured in your AP) is 50 ms.
		If the AP timeout is set too low, it may decrease the bandwidth and roaming performance.
		[FW:E2080.AC.1:5.52.0]
		"
	::= {bridgeRoamingAdvanced 5}

-- End bridge filter
--***********************

--Bridge status scan
bridgeWileressScanTable OBJECT-TYPE
    SYNTAX  SEQUENCE OF BridgeWirelessScanEntry
    MAX-ACCESS  not-accessible
    STATUS  current
    DESCRIPTION
        "Significant only in MAX-ACCESS POINT mode.
		This table shows information AP bridge filtering rules list.
		[FW:E2080.AC.1:5.52.0]"
    ::= { bridgeWirelessScan 1 }


bridgeWirelessScanEntry OBJECT-TYPE
    SYNTAX  BridgeWirelessScanEntry
    MAX-ACCESS  not-accessible
    STATUS  current
	DESCRIPTION "Shows information of the rule.
		[FW:E2080.AC.1:5.52.0]
		"
    INDEX   { bridgeWirelessScanAPMac }
    ::= { bridgeWileressScanTable 1 }

BridgeWirelessScanEntry ::=
	SEQUENCE {
		bridgeWirelessScanAPMac
			PhysAddress,
		bridgeWirelessScanSSID
			OCTET STRING,
		bridgeWirelessScanChannel
			INTEGER,
		bridgeWirelessScanMode
			INTEGER,
		bridgeWirelessScanSecurity
			INTEGER,
		bridgeWirelessScanRssi
			INTEGER
	}

bridgeWirelessScanAPMac OBJECT-TYPE
    SYNTAX PhysAddress
    MAX-ACCESS read-only
    STATUS current
    DESCRIPTION "MAC address of the access point.
		[FW:E2080.AC.1:5.52.0]"
    ::= { bridgeWirelessScanEntry 1 }

bridgeWirelessScanSSID OBJECT-TYPE
    SYNTAX  OCTET STRING (SIZE (0..33))
    MAX-ACCESS read-only
    STATUS current
    DESCRIPTION "[FW:E2080.AC.1:5.52.0]"
    ::= { bridgeWirelessScanEntry 2 }

bridgeWirelessScanChannel OBJECT-TYPE
    SYNTAX INTEGER
    MAX-ACCESS read-only
    STATUS current
    DESCRIPTION "[FW:E2080.AC.1:5.52.0]"
    ::= { bridgeWirelessScanEntry 3 }


bridgeWirelessScanMode OBJECT-TYPE
    SYNTAX INTEGER {
		b-only(1),
		g-only(2),
		mixed-b-g(3),
		a-only(4)
    }
    MAX-ACCESS read-only
    STATUS current
    DESCRIPTION "Show AP's IEEE 802.11x compatibility mode.
		[FW:E2080.AC.1:5.52.0]"
    ::= { bridgeWirelessScanEntry 4 }

bridgeWirelessScanSecurity OBJECT-TYPE
    SYNTAX INTEGER {
    		none(0),
			wep(1),
			wpa(2)
		}
    MAX-ACCESS read-only
    STATUS current
    DESCRIPTION "[FW:E2080.AC.1:5.52.0]"
    ::= { bridgeWirelessScanEntry 5 }

bridgeWirelessScanRssi OBJECT-TYPE
    SYNTAX INTEGER
    MAX-ACCESS read-only
    STATUS current
    DESCRIPTION "[FW:E2080.AC.1:5.52.0]"
    ::= { bridgeWirelessScanEntry 6 }



--end bridge status scan

--BrigeNAT
brigeNATStatus OBJECT-TYPE
    SYNTAX INTEGER {
    		disable(1),
			enable(2)
		}
    MAX-ACCESS read-write
    STATUS current
    DESCRIPTION "Enable / disable NAT
		[FW:E2080.AC.1:5.52.0]
		"
    ::= { bridgeNAT 1 }

brigeNATEnablePing OBJECT-TYPE
    SYNTAX INTEGER {
    		disable(1),
			enable(2)
		}
    MAX-ACCESS read-write
    STATUS current
    DESCRIPTION "Enable / disable ping response from WAN
		[FW:E2080.AC.1:5.52.0]
		"
    ::= { bridgeNAT 2 }

brigeNATEnableProductWebServer OBJECT-TYPE
    SYNTAX INTEGER {
    		disable(1),
			enable(2)
		}
    MAX-ACCESS read-write
    STATUS current
    DESCRIPTION "Enable / disable the internal web server from WAN
		[FW:E2080.AC.1:5.52.0]
		"
    ::= { bridgeNAT 3 }

brigeNATInternalWebServerPort OBJECT-TYPE
    SYNTAX INTEGER
    MAX-ACCESS read-write
    STATUS current
    DESCRIPTION "TCP port used by internal web server from WAN
		[FW:E2080.AC.1:5.52.0]
		"
    ::= { bridgeNAT 4 }

brigeNATEnableProductSnmpServer OBJECT-TYPE
    SYNTAX INTEGER {
    		disable(1),
			enable(2)
		}
    MAX-ACCESS read-write
    STATUS current
    DESCRIPTION "Enable / disable the internal snmp server from WAN
		[FW:E2080.AC.1:5.52.0]
		"
    ::= { bridgeNAT 5 }

brigeNATInternalWebSnmpPort OBJECT-TYPE
    SYNTAX INTEGER
    MAX-ACCESS read-write
    STATUS current
    DESCRIPTION "TCP port used by internal snmp server from WAN
		[FW:E2080.AC.1:5.52.0]
		"
    ::= { bridgeNAT 6 }


brigeNATWanIpAddrMode OBJECT-TYPE
    SYNTAX  INTEGER {static(1),dhcp(2)}
    MAX-ACCESS read-write
    STATUS current
    DESCRIPTION "Ip address mode on wan side
		[FW:E2080.AC.1:5.52.0]
		"
    ::= { bridgeNAT 7 }

brigeNATWanIpAddr OBJECT-TYPE
    SYNTAX  IpAddress
    MAX-ACCESS read-write
    STATUS current
    DESCRIPTION "Static Ip address on wan side
		[FW:E2080.AC.1:5.52.0]
		"
    ::= { bridgeNAT 8 }

brigeNATWanSubnetMask OBJECT-TYPE
    SYNTAX  IpAddress
    MAX-ACCESS read-write
    STATUS current
    DESCRIPTION "Subnet mask on wan side
		[FW:E2080.AC.1:5.52.0]
		"
    ::= { bridgeNAT 9 }

brigeNATWanGateway OBJECT-TYPE
    SYNTAX  IpAddress
    MAX-ACCESS read-write
    STATUS current
    DESCRIPTION "Gateway ip address on wan side
		[FW:E2080.AC.1:5.52.0]
		"
    ::= { bridgeNAT 10 }

	bridgeNatPortForwardingName OBJECT-TYPE
    SYNTAX  OCTET STRING (SIZE (0..20))
    MAX-ACCESS  read-write
    STATUS current
    DESCRIPTION "Show rule's name
		[FW:E2080.AC.1:5.52.0]
		"
    ::= { bridgeNatPortForwarding 2 }

	bridgeNatPortForwardingIpAddr OBJECT-TYPE
    SYNTAX  IpAddress
    MAX-ACCESS read-write
    STATUS current
    DESCRIPTION "Show ipaddress to forward data
		[FW:E2080.AC.1:5.52.0]
		"
    ::= { bridgeNatPortForwarding 3 }

	bridgeNatPortForwardingPublicTcpPort OBJECT-TYPE
    SYNTAX   OCTET STRING (SIZE (0..20))
    MAX-ACCESS  read-write
    STATUS current
    DESCRIPTION "Show public TCP port
		[FW:E2080.AC.1:5.52.0]
		"
    ::= { bridgeNatPortForwarding 4 }

	bridgeNatPortForwardingPrivateTcpPort OBJECT-TYPE
    SYNTAX   OCTET STRING (SIZE (0..20))
    MAX-ACCESS  read-write
    STATUS current
    DESCRIPTION	"Show private TCP port
		[FW:E2080.AC.1:5.52.0]
		"
    ::= { bridgeNatPortForwarding 5 }

	bridgeNatPortForwardingPublicUdpPort OBJECT-TYPE
    SYNTAX   OCTET STRING (SIZE (0..20))
    MAX-ACCESS  read-write
    STATUS current
    DESCRIPTION "Show public TCP port
		[FW:E2080.AC.1:5.52.0]
		"
    ::= { bridgeNatPortForwarding 6 }

	bridgeNatPortForwardingPrivateUdpPort OBJECT-TYPE
    SYNTAX   OCTET STRING (SIZE (0..20))
    MAX-ACCESS  read-write
    STATUS current
    DESCRIPTION "Show private TCP port
		[FW:E2080.AC.1:5.52.0]
		"
    ::= { bridgeNatPortForwarding 7 }

bridgeNatPortForwardingEnableRule OBJECT-TYPE
    SYNTAX  INTEGER
    MAX-ACCESS  read-write
    STATUS current
    DESCRIPTION "when writed, enable the rule which is indexed by the written value
		[FW:E2080.AC.1:5.52.0]
		"
    ::= { bridgeNatPortForwarding 8 }

bridgeNatPortForwardingDisableRule OBJECT-TYPE
    SYNTAX  INTEGER
    MAX-ACCESS  read-write
    STATUS current
    DESCRIPTION	"when writed, disable the rule which is indexed by the written value
		[FW:E2080.AC.1:5.52.0]
		"
    ::= { bridgeNatPortForwarding 9 }

bridgeNatPortForwardingSaveRule OBJECT-TYPE
    SYNTAX  INTEGER
    MAX-ACCESS  read-write
    STATUS current
    DESCRIPTION "when writed, save the rule which is indexed by the written value
		[FW:E2080.AC.1:5.52.0]
		"
    ::= { bridgeNatPortForwarding 10 }

bridgeNatPortForwardingDeleteRule OBJECT-TYPE
    SYNTAX  INTEGER
    MAX-ACCESS read-write
    STATUS current
    DESCRIPTION "when writed, delete the rule which is indexed by the written value
		[FW:E2080.AC.1:5.52.0]
		"
    ::= { bridgeNatPortForwarding 11 }

bridgeNatPortForwardingTable OBJECT-TYPE
	SYNTAX SEQUENCE OF BridgeNatPortForwardingEntry
	MAX-ACCESS not-accessible
	STATUS current
	DESCRIPTION "This table show information on port forwading rules
		[FW:E2080.AC.1:5.52.0]"
	::= { bridgeNatPortForwarding 1 }

bridgeNatPortForwardingEntry OBJECT-TYPE
	SYNTAX BridgeNatPortForwardingEntry
	MAX-ACCESS not-accessible
	STATUS current
	DESCRIPTION "Shows information of rule.
		[FW:E2080.AC.1:5.52.0]
		"
	INDEX { bridgeNatPortForwardingListId }
	::= {bridgeNatPortForwardingTable 1}

BridgeNatPortForwardingEntry ::=
	SEQUENCE {
		bridgeNatPortForwardingListId
			INTEGER,
		bridgeNatPortForwardingListEnable
			INTEGER,
		bridgeNatPortForwardingListName
			OCTET STRING,
		bridgeNatPortForwardingListIpAddr
			IpAddress,
		bridgeNatPortForwardingListPublicTcpPort
			OCTET STRING,
		bridgeNatPortForwardingListPrivateTcpPort
			OCTET STRING,
		bridgeNatPortForwardingListPublicUdpPort
			OCTET STRING,
		bridgeNatPortForwardingListPrivateUdpPort
			OCTET STRING
	}

	bridgeNatPortForwardingListId OBJECT-TYPE
    SYNTAX  INTEGER
    MAX-ACCESS read-only
    STATUS current
    DESCRIPTION "Rule index
		[FW:E2080.AC.1:5.52.0]"
    ::= { bridgeNatPortForwardingEntry 1 }

	bridgeNatPortForwardingListName OBJECT-TYPE
    SYNTAX  OCTET STRING (SIZE (0..20))
    MAX-ACCESS read-only
    STATUS current
    DESCRIPTION "Show rule's name
		[FW:E2080.AC.1:5.52.0]"
    ::= { bridgeNatPortForwardingEntry 2 }

	bridgeNatPortForwardingListIpAddr OBJECT-TYPE
    SYNTAX  IpAddress
    MAX-ACCESS read-only
    STATUS current
    DESCRIPTION "Show ipaddress to forward data
		[FW:E2080.AC.1:5.52.0]"
    ::= { bridgeNatPortForwardingEntry 3 }

	bridgeNatPortForwardingListPublicTcpPort OBJECT-TYPE
    SYNTAX   OCTET STRING (SIZE (0..20))
    MAX-ACCESS read-only
    STATUS current
    DESCRIPTION "Show public TCP port
		[FW:E2080.AC.1:5.52.0]"
    ::= { bridgeNatPortForwardingEntry 4 }

	bridgeNatPortForwardingListPrivateTcpPort OBJECT-TYPE
    SYNTAX   OCTET STRING (SIZE (0..20))
    MAX-ACCESS read-only
    STATUS current
    DESCRIPTION "Show private TCP port
		[FW:E2080.AC.1:5.52.0]"
    ::= { bridgeNatPortForwardingEntry 5 }

	bridgeNatPortForwardingListPublicUdpPort OBJECT-TYPE
    SYNTAX   OCTET STRING (SIZE (0..20))
    MAX-ACCESS read-only
    STATUS current
    DESCRIPTION "Show public TCP port
		[FW:E2080.AC.1:5.52.0]"
    ::= { bridgeNatPortForwardingEntry 6 }

	bridgeNatPortForwardingListPrivateUdpPort OBJECT-TYPE
    SYNTAX   OCTET STRING (SIZE (0..20))
    MAX-ACCESS read-only
    STATUS current
    DESCRIPTION "Show private TCP port
		[FW:E2080.AC.1:5.52.0]"
    ::= { bridgeNatPortForwardingEntry 7 }

	bridgeNatPortForwardingListEnable OBJECT-TYPE
    SYNTAX  INTEGER {
		disable(1),
		enable(2)}
    MAX-ACCESS read-only
    STATUS current
    DESCRIPTION "Rule state
		[FW:E2080.AC.1:5.52.0]"
    ::= { bridgeNatPortForwardingEntry 8 }

--end bridgeNAT
--*********************

-- Administration group

adminReset OBJECT-TYPE
	SYNTAX  INTEGER {reset(1)}
	MAX-ACCESS  read-write
	STATUS  current
	DESCRIPTION "
		Writing 1 resets the product. This must be done after each configuration change.
		[FW:E2080.AC.1:5.52.0]
		[FW:E2148.AC.1:2.8.0.1]

	"
	::= { administration 1}

adminResetFactory OBJECT-TYPE
	SYNTAX  INTEGER {resetfactory(1)}
	MAX-ACCESS  read-write
	STATUS  current
	DESCRIPTION "
		Writing 1 resets the product to the factory settings.
		[FW:E2080.AC.1:5.52.0]
		[FW:E2148.AC.1:2.8.0.1]

	"
	::= { administration 2}

adminEnableWebServer OBJECT-TYPE
    SYNTAX DisableEnable
    MAX-ACCESS read-write
    STATUS current
    DESCRIPTION
    	" Enable or Disable internal webserver.
		Not supported on the WLn- products series.
		[FW:E2080.AC.1:5.52.0]

	"
    ::= { administration 3}

adminAutoSave OBJECT-TYPE
    SYNTAX DisableEnable
    MAX-ACCESS read-write
    STATUS current
    DESCRIPTION
    	" Enable or Disable the automatic saving of changes. When this function is disabled, modifications are not saved automatically after change and some OID are applied immediately.
		Not supported on the WLn- products series.
		[FW:E2080.AC.1:5.52.0]

	"
    ::= { administration 4}

adminSave OBJECT-TYPE
    SYNTAX INTEGER {
			saveNotRequired(3),
			saveRequired(2),
			save(1)
		}
    MAX-ACCESS read-write
    STATUS current
    DESCRIPTION
    	" Write 1 to save the modification in flash. Read this OID to know if a save is require.
		[FW:E2080.AC.1:5.52.0]
		[FW:E2148.AC.1:2.8.0.1]

		"
    ::= { administration 5}

adminApply OBJECT-TYPE
	SYNTAX INTEGER {
			disable(1),
			enable(2),
			applyRequire(3)
		}
	MAX-ACCESS read-write
	STATUS current
	DESCRIPTION "
			When set to 'Enable', applies configuration
			changes without rebooting the product. The value
			returns to 'Disable' after execution.
			The value return 'apply_require' if the configuration
			was modified but not applied.
			[FW:E2148.AC.1:2.8.0.1]
			[SYNFW:3:E2148.AC.1:4.10.0.1]
		"
	::= { administration 6}

adminConfigHash OBJECT-TYPE
    SYNTAX  OCTET STRING (SIZE (0..32))
	MAX-ACCESS read-only STATUS current
	DESCRIPTION "Hash value of configuration file
		[FW:E2148.AC.1:3.14.0.1]
		"
	::= { administration 7}

fileTransfer OBJECT IDENTIFIER ::= { administration 8 }

adminIdentify OBJECT-TYPE
	SYNTAX INTEGER
	MAX-ACCESS read-write STATUS current
	DESCRIPTION "Flash the product diagnostic LED.
		     Return 0 after get.
		     [FW:E2148.AC.1:3.14.0.1]
		    "
	::= { administration 9}

adminEvents OBJECT IDENTIFIER ::= { administration 10 }

adminTimeZone OBJECT IDENTIFIER ::= { administration 11 }

adminSystemDateAndTime OBJECT IDENTIFIER ::= { administration 12 }

--  fileTransfer group

fileTransferAction OBJECT-TYPE
	SYNTAX INTEGER {upload(1), download(2)}
	MAX-ACCESS read-write STATUS current
	DESCRIPTION "file {upload to/download from} product
		[FW:E2148.AC.1:3.14.0.1]"
	::= { fileTransfer 1}

fileTransferType OBJECT-TYPE
	SYNTAX INTEGER {
		config(1),
		firmware(2),
		lte-firmware(3),
		wids-config(4),
		ssh-auth-keys(5)
	}
	MAX-ACCESS read-write STATUS current
	DESCRIPTION "Type of file to transfer: 1.configuration back up;
		2.firmware file; 3.LTE radio firmware; 4.WIDS configuration
		[FW:E2148.AC.1:3.14.0.1]"
	::= { fileTransfer 2}

fileTransferSize OBJECT-TYPE
	SYNTAX INTEGER MAX-ACCESS read-write STATUS current
	DESCRIPTION "Maximum size of file chunks to transfer
		[FW:E2148.AC.1:3.14.0.1]"
	::= { fileTransfer 3}

fileTransferIndex OBJECT-TYPE
	SYNTAX INTEGER MAX-ACCESS read-write STATUS current
	DESCRIPTION "Index of chunk to transfer
		[FW:E2148.AC.1:3.14.0.1]"
	::= { fileTransfer 4}

fileTransferHash OBJECT-TYPE
	SYNTAX OCTET STRING MAX-ACCESS read-write STATUS current
	DESCRIPTION "Hash value of file to transfer
		[FW:E2148.AC.1:3.14.0.1]"
	::= { fileTransfer 5}

fileTransferChunk OBJECT-TYPE
	SYNTAX OCTET STRING MAX-ACCESS read-write STATUS current
	DESCRIPTION "File chunk to transfer; includes
		Size bytes at file offset Index*Size
		[FW:E2148.AC.1:3.14.0.1]"
	::= { fileTransfer 6}

fileTransferResult OBJECT-TYPE
	SYNTAX INTEGER {available(1), in-progress(2), nok(3)}
	MAX-ACCESS read-only STATUS current
	DESCRIPTION "Transfer result
		[FW:E2148.AC.1:3.14.0.1]"
	::= { fileTransfer 7}

fileTransferSession OBJECT-TYPE
	SYNTAX INTEGER
	MAX-ACCESS read-only STATUS current
	DESCRIPTION "Transfer session
		[FW:E2148.AC.1:3.14.0.1]"
	::= { fileTransfer 8}

--  Event Handler interactions group

adminEventDisable OBJECT-TYPE
	SYNTAX OCTET STRING MAX-ACCESS read-write STATUS current
	DESCRIPTION "Disable (i.e. reset) action for the named alarm
		[FW:E2148.AC.1:4.12.0.1]"
	::= { adminEvents 1}

adminEventEnable OBJECT-TYPE
	SYNTAX OCTET STRING MAX-ACCESS read-write STATUS current
	DESCRIPTION "Enable (i.e. set) action for the named alarm
		[FW:E2148.AC.1:4.12.0.1]"
	::= { adminEvents 2}

adminEventTrigger OBJECT-TYPE
	SYNTAX OCTET STRING MAX-ACCESS read-write STATUS current
	DESCRIPTION "Execute action for the named one-shot alarm
		[FW:E2148.AC.1:4.12.0.1]"
	::= { adminEvents 3}

-- Admin Time Zone

adminTimeZoneDBVersion OBJECT-TYPE
	SYNTAX DisplayString
	MAX-ACCESS read-only
	STATUS current
	DESCRIPTION
		"Returns the iana Time Zone Database version
			Please see: https://www.iana.org/time-zones

			[FW:E2148.AC.1:4.16.0.1]"
	::= { adminTimeZone 1 }

adminTimeZoneName OBJECT-TYPE
    	SYNTAX OCTET STRING (SIZE (1..255))
	MAX-ACCESS read-write STATUS current
	DESCRIPTION "Set Time Zone name as defined in the iana Time Zone Database
			Please see: https://www.iana.org/time-zones

			example:
			(This an extract from the database, but it may not be up-to-date)

			America/New York
			Europe/Paris

			[FW:E2148.AC.1:4.16.0.1]
		"
	::= { adminTimeZone 2}

-- Admin Sytem date and Time

adminSystemDateAndTimeLocal OBJECT-TYPE
    	SYNTAX DateAndTime
	MAX-ACCESS read-write STATUS current
	DESCRIPTION "The system current date and time expressed relative to the
			configured Time Zone.
			For Write operation, only 8 OCTETs can be set, as the 3 remaining
			octets reserved for the direction from UTC, are automatically
			deduced from the Configured Time Zone.
			For Read operation, 11 OCTETs will be returned.

			For this configuration, you don't need to make Save and Apply

			[FW:E2148.AC.1:4.16.0.1]
"
	::= { adminSystemDateAndTime 1}

adminSystemDateAndTimeUTC OBJECT-TYPE
    	SYNTAX DateAndTime
	MAX-ACCESS read-write STATUS current
	DESCRIPTION "The system current date and time expressed in UTC.
			For Write operation, only 8 OCTETs can be set, as the 3 remaining
			octets reserved for the direction from UTC, are meaningless.
			For Read operation, only 8 OCTETs will be returned, as the 3
			octets reserved for the direction from UTC, are meaningless.

			For this configuration, you don't need to make Save and Apply

			[FW:E2148.AC.1:4.16.0.1]
"
	::= { adminSystemDateAndTime 2}

-- os-stat  group
os-statFreeHeap OBJECT-TYPE
    SYNTAX INTEGER
    MAX-ACCESS read-only
    STATUS current
    DESCRIPTION
        "
		The amount of memory currently available, measured in bytes.
		[FW:E2080.AC.1:5.52.0]
		"
    ::= { os-stat  1 }

os-statTotalHeap OBJECT-TYPE
    SYNTAX INTEGER
    MAX-ACCESS read-only
    STATUS current
    DESCRIPTION
        "
		The total size of the heap, measured in bytes.
		[FW:E2080.AC.1:5.52.0]
		"
    ::= { os-stat  2 }

os-statHeapLowWater OBJECT-TYPE
    SYNTAX INTEGER
    MAX-ACCESS read-only
    STATUS current
    DESCRIPTION
        "
		Low water mark for the heap. Writing any value this variable will always
	    reset the low water to the total heap size.
		[FW:E2080.AC.1:5.52.0]
	    "
    ::= { os-stat  3 }

os-statNetpageFree OBJECT-TYPE
    SYNTAX INTEGER
    MAX-ACCESS read-only
    STATUS current
    DESCRIPTION
        "
		The amount of netpages currently available, measured in bytes.
		[FW:E2080.AC.1:5.52.0]
	    "
    ::= { os-stat  4 }

os-statNetpageLowWater OBJECT-TYPE
    SYNTAX INTEGER
    MAX-ACCESS read-only
    STATUS current
    DESCRIPTION
        "
		Low water mark for the netpage.
		[FW:E2080.AC.1:5.52.0]
	    "
    ::= { os-stat  5 }


-- wlg-aboard group
wlg-aboard-PW1-state OBJECT-TYPE
    SYNTAX INTEGER {powerOff(1), powerOn(2)}
    MAX-ACCESS read-only
    STATUS obsolete
    DESCRIPTION
	    "
		Power 1 state
		[FW:E2080.AC.1:5.52.0]
	    "
    ::= { wlg-aboard  1 }

wlg-aboard-PW2-state OBJECT-TYPE
    SYNTAX INTEGER {powerOff(1), powerOn(2)}
    MAX-ACCESS read-only
    STATUS obsolete
    DESCRIPTION
	    "
		Power 2 state
		[FW:E2080.AC.1:5.52.0]
	    "
    ::= { wlg-aboard  2 }

-- lanInterface group
lanInterfaceIpAddrMode OBJECT-TYPE
    SYNTAX  INTEGER {static(1),dhcp(2)}
    MAX-ACCESS  read-write
    STATUS  current
    DESCRIPTION
        "Static or DHCP Ip settings
		[FW:E2080.AC.1:5.52.0]
		"

    ::= { lanInterface 1 }

lanInterfaceIpAddr OBJECT-TYPE
    SYNTAX  IpAddress
    MAX-ACCESS  read-write
    STATUS  current
    DESCRIPTION
		"Product IP address
		[FW:E2080.AC.1:5.52.0]
		"
    ::= { lanInterface 2 }

lanInterfaceSubNetMask OBJECT-TYPE
    SYNTAX  IpAddress
    MAX-ACCESS  read-write
    STATUS  current
    DESCRIPTION
		"Network mask
		[FW:E2080.AC.1:5.52.0]
		"
    ::= { lanInterface 3 }

lanInterfaceGatewayIp OBJECT-TYPE
    SYNTAX  IpAddress
    MAX-ACCESS  read-write
    STATUS  current
    DESCRIPTION
		"IP gateway
		[FW:E2080.AC.1:5.52.0]
		"
    ::= { lanInterface 4 }

lanInterfaceHostName OBJECT-TYPE
    SYNTAX  OCTET STRING (SIZE (1..64))
    MAX-ACCESS  read-write
    STATUS  current
    DESCRIPTION
		"Host name
		[FW:E2080.AC.1:5.52.0]
		"
    ::= { lanInterface 5 }

lanInterfaceLocalDomainName OBJECT-TYPE
    SYNTAX  OCTET STRING (SIZE (1..33))
    MAX-ACCESS  read-write
    STATUS  current
    DESCRIPTION
		"Local Domain Name
		[FW:E2080.AC.1:5.52.0]
		"
    ::= { lanInterface 6 }

-- c-key-management
ckeyManagementCopySettingTo OBJECT-TYPE
    SYNTAX  INTEGER
    MAX-ACCESS  read-write
    STATUS  current
    DESCRIPTION
		"
		Write 1 to copy the current settings to the C-KEY. After this action, all previous data in the C-KEY are lost.
		[FW:E2080.AC.1:5.52.0]
		[FW:E2148.AC.1:2.8.0.1]

		"
    ::= { c-key-management 1 }

ckeyManagementCopySettingFrom OBJECT-TYPE
    SYNTAX  INTEGER
    MAX-ACCESS  read-write
    STATUS  current
    DESCRIPTION
		"
		Write 1 to copy the product settings from the C-KEY. On WLn series, this will reboot the product.
		[FW:E2080.AC.1:5.52.0]
		[FW:E2148.AC.1:2.8.0.1]

		"
    ::= { c-key-management 2 }

ckeyManagementErase OBJECT-TYPE
    SYNTAX  INTEGER
    MAX-ACCESS  read-write
    STATUS  current
    DESCRIPTION
		"
		Write 1 to erase the C-KEY.
		[FW:E2148.AC.1:2.8.0.1]

		"
    ::= { c-key-management 3 }

ckeyManagementStatus OBJECT-TYPE
    SYNTAX  INTEGER {
		ckeyStatusNotDetected(1),
		ckeyStatusNotValid(2),
		ckeyStatusValidAndApplied(3),
		ckeyStatusValidAndBackup(4),
		ckeyStatusValidAndIgnored(5),
		ckeyStatusContainsWlg(6),
		ckeyStatusTooSmall(7),
		ckeyStatusWrongProduct(8),
		ckeyStatusIgnored(9),
		ckeyStatusBusy(10)
	}
    MAX-ACCESS  read-only
    STATUS  current
    DESCRIPTION
		"
		Read the C-Key status
		[FW:E2148.AC.1:2.8.0.1]

		"
    ::= { c-key-management 4 }

ckeyManagementIgnoreSetting OBJECT-TYPE
    SYNTAX  DisableEnable
    MAX-ACCESS  read-write
    STATUS  current
    DESCRIPTION
		"
		Write 2(enable) to disallow configuration loading from C-Key at startup.
		Write 1(disable) to allow configuration loading from C-Key at startup.
		[FW:E2148.AC.1:2.8.0.1]

		"
    ::= { c-key-management 5 }

ckeyManagementDisableLed OBJECT-TYPE
    SYNTAX  DisableEnable
    MAX-ACCESS  read-write
    STATUS  current
    DESCRIPTION
		"
		Write 2(enable) to make the C-Key status red LED stayed off.
		Write 1(disable) to use the C-Key status red LED as usal.
		[FW:E2148.AC.1:2.8.0.1]

		"
    ::= { c-key-management 6 }


ckeyManagementTest OBJECT-TYPE
    SYNTAX  INTEGER
    MAX-ACCESS  read-write
    STATUS  current
    DESCRIPTION
		"
		Write 1 to start the C-Key auto-test.
		Warning, this test will erase the whole C-Key.
		This OID is reserved for ACKSYS production.
		[FW:E2148.AC.1:2.8.0.1]

		"
    ::= { c-key-management 7 }

ckeyManagementTestResult OBJECT-TYPE
    SYNTAX  INTEGER {
		ckeyTestInternalError(1),
		ckeyTestNotAvailAble(2),
		ckeyTestInProgress(3),
		ckeyTestNotOk(4),
		ckeyTestOk(5)
	}
    MAX-ACCESS  read-only
    STATUS  current
    DESCRIPTION
		"
		Read the C-Key test results
		This OID is reserved for ACKSYS production.
		[FW:E2148.AC.1:2.8.0.1]

		"
    ::= { c-key-management 8 }

-- alarmSettings
alarmSettingsTest OBJECT-TYPE
    SYNTAX  INTEGER {set(1),clear(2)}
    MAX-ACCESS  read-write
    STATUS  current
    DESCRIPTION
		"
		Allow to get and set the alarm output status.
		[FW:E2080.AC.1:5.52.0]
		"
    ::= { alarmSettings 1 }

alarmSettingsPower1DownEnable OBJECT-TYPE
    SYNTAX DisableEnable
    MAX-ACCESS  read-write
    STATUS  current
    DESCRIPTION
		"
		[FW:E2080.AC.1:5.52.0]
		"
    ::= { alarmSettingsPower1Down 1 }

alarmSettingsPower1DownEnableAutomaticReset OBJECT-TYPE
    SYNTAX DisableEnable
    MAX-ACCESS  read-write
    STATUS  current
    DESCRIPTION
		"
		[FW:E2080.AC.1:5.52.0]
		"
    ::= { alarmSettingsPower1Down 2 }

alarmSettingsPower1DownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsPower1Down 3 }

alarmSettingsPower2DownEnable OBJECT-TYPE
    SYNTAX DisableEnable
    MAX-ACCESS  read-write
    STATUS  current
    DESCRIPTION
		"
		[FW:E2080.AC.1:5.52.0]
		"
    ::= { alarmSettingsPower2Down 1 }

alarmSettingsPower2DownEnableAutomaticReset OBJECT-TYPE
    SYNTAX DisableEnable
    MAX-ACCESS  read-write
    STATUS  current
    DESCRIPTION
		"
		[FW:E2080.AC.1:5.52.0]
		"
    ::= { alarmSettingsPower2Down 2 }

alarmSettingsPower2DownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsPower2Down 3 }

alarmSettingsLan1DownEnable OBJECT-TYPE
    SYNTAX DisableEnable
    MAX-ACCESS  read-write
    STATUS  current
    DESCRIPTION
		"
		[FW:E2080.AC.1:5.52.0]
		"
    ::= { alarmSettingsLan1Down 1 }

alarmSettingsLan1DownEnableAutomaticReset OBJECT-TYPE
    SYNTAX DisableEnable
    MAX-ACCESS  read-write
    STATUS  current
    DESCRIPTION
		"
		[FW:E2080.AC.1:5.52.0]
		"
    ::= { alarmSettingsLan1Down 2 }

alarmSettingsLan1DownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsLan1Down 3 }

alarmSettingsLan2DownEnable OBJECT-TYPE
    SYNTAX DisableEnable
    MAX-ACCESS  read-write
    STATUS  current
    DESCRIPTION
		"
		[FW:E2080.AC.1:5.52.0]
		"
    ::= { alarmSettingsLan2Down 1 }

alarmSettingsLan2DownEnableAutomaticReset OBJECT-TYPE
    SYNTAX DisableEnable
    MAX-ACCESS  read-write
    STATUS  current
    DESCRIPTION
		"
		[FW:E2080.AC.1:5.52.0]
		"
    ::= { alarmSettingsLan2Down 2 }

alarmSettingsLan2DownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsLan2Down 3 }

alarmSettingsLan3DownEnable OBJECT-TYPE
    SYNTAX DisableEnable
    MAX-ACCESS  read-write
    STATUS  current
    DESCRIPTION
		"
		[FW:E2080.AC.1:5.52.0]
		"
    ::= { alarmSettingsLan3Down 1 }

alarmSettingsLan3DownEnableAutomaticReset OBJECT-TYPE
    SYNTAX DisableEnable
    MAX-ACCESS  read-write
    STATUS  current
    DESCRIPTION
		"
		[FW:E2080.AC.1:5.52.0]
		"
    ::= { alarmSettingsLan3Down 2 }

alarmSettingsLan3DownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsLan3Down 3 }

alarmSettingsLan4DownEnable OBJECT-TYPE
    SYNTAX DisableEnable
    MAX-ACCESS  read-write
    STATUS  current
    DESCRIPTION
		"
		[FW:E2080.AC.1:5.52.0]
		"
    ::= { alarmSettingsLan4Down 1 }

alarmSettingsLan4DownEnableAutomaticReset OBJECT-TYPE
    SYNTAX DisableEnable
    MAX-ACCESS  read-write
    STATUS  current
    DESCRIPTION
		"
		[FW:E2080.AC.1:5.52.0]
		"
    ::= { alarmSettingsLan4Down 2 }

alarmSettingsLan4DownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsLan4Down 3 }

alarmSettingsLan5DownEnable OBJECT-TYPE
    SYNTAX DisableEnable
    MAX-ACCESS  read-write
    STATUS  current
    DESCRIPTION
		"
		[FW:E2080.AC.1:5.52.0]
		"
    ::= { alarmSettingsLan5Down 1 }

alarmSettingsLan5DownEnableAutomaticReset OBJECT-TYPE
    SYNTAX DisableEnable
    MAX-ACCESS  read-write
    STATUS  current
    DESCRIPTION
		"
		[FW:E2080.AC.1:5.52.0]
		"
    ::= { alarmSettingsLan5Down 2 }

alarmSettingsLan5DownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsLan5Down 3 }

alarmSettingsLan6DownEnable OBJECT-TYPE
    SYNTAX DisableEnable
    MAX-ACCESS  read-write
    STATUS  current
    DESCRIPTION
		"
		[FW:E2080.AC.1:5.52.0]
		"
    ::= { alarmSettingsLan6Down 1 }

alarmSettingsLan6DownEnableAutomaticReset OBJECT-TYPE
    SYNTAX DisableEnable
    MAX-ACCESS  read-write
    STATUS  current
    DESCRIPTION
		"
		[FW:E2080.AC.1:5.52.0]
		"
    ::= { alarmSettingsLan6Down 2 }

alarmSettingsLan6DownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsLan6Down 3 }

alarmSettingsLan7DownEnable OBJECT-TYPE
    SYNTAX DisableEnable
    MAX-ACCESS  read-write
    STATUS  current
    DESCRIPTION
		"
		[FW:E2080.AC.1:5.52.0]
		"
    ::= { alarmSettingsLan7Down 1 }

alarmSettingsLan7DownEnableAutomaticReset OBJECT-TYPE
    SYNTAX DisableEnable
    MAX-ACCESS  read-write
    STATUS  current
    DESCRIPTION
		"
		[FW:E2080.AC.1:5.52.0]
		"
    ::= { alarmSettingsLan7Down 2 }

alarmSettingsLan7DownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsLan7Down 3}

alarmSettingsLan8DownEnable OBJECT-TYPE
    SYNTAX DisableEnable
    MAX-ACCESS  read-write
    STATUS  current
    DESCRIPTION
		"
		[FW:E2080.AC.1:5.52.0]
		"
    ::= { alarmSettingsLan8Down 1 }

alarmSettingsLan8DownEnableAutomaticReset OBJECT-TYPE
    SYNTAX DisableEnable
    MAX-ACCESS  read-write
    STATUS  current
    DESCRIPTION
		"
		[FW:E2080.AC.1:5.52.0]
		"
    ::= { alarmSettingsLan8Down 2 }

alarmSettingsLan8DownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsLan8Down 3 }
alarmSettingsWLANDownEnable OBJECT-TYPE
    SYNTAX  INTEGER {disable(1),enable(2)}
    MAX-ACCESS  read-write
    STATUS  current
    DESCRIPTION
		"
		[FW:E2080.AC.1:5.52.0]
		"
    ::= { alarmSettingsWLANDown 1 }

alarmSettingsWLANDownEnableAutomaticReset OBJECT-TYPE
    SYNTAX  INTEGER {disable(1),enable(2)}
    MAX-ACCESS  read-write
    STATUS  current
    DESCRIPTION
		"
		[FW:E2080.AC.1:5.52.0]
		"
    ::= { alarmSettingsWLANDown 2 }

alarmSettingsWLANDownStatus OBJECT-TYPE
    SYNTAX  INTEGER {disable(1),enable(2),ack(3)}
    MAX-ACCESS  read-write
    STATUS  current
    DESCRIPTION
		"
		Read to know the alarm source status (disable / enable )
		Write 3 to acknowledge the alarm source.
		[FW:E2080.AC.1:5.52.0]

		"
    ::= { alarmSettingsWLANDown 3 }

-- powerStatus
powerStatus-PW1-state OBJECT-TYPE
    SYNTAX INTEGER {powerOff(1), powerOn(2)}
    MAX-ACCESS read-only
    STATUS current
    DESCRIPTION
	    "
		Power 1 state
		[FW:E2080.AC.1:5.52.0]
		[FW:E2148.AC.1:3.14.0.1]
	    "
    ::= { powerStatus  1 }

powerStatus-PW2-state OBJECT-TYPE
    SYNTAX INTEGER {powerOff(1), powerOn(2)}
    MAX-ACCESS read-only
    STATUS current
    DESCRIPTION
	    "
		Power 2 state
		[FW:E2080.AC.1:5.52.0]
		[FW:E2148.AC.1:3.14.0.1]
	    "
    ::= { powerStatus  2 }
--***********************
-- Serial interface

-- ------------------------
-- +++ Serial format +++

serialFormatBaudRate OBJECT-TYPE
    SYNTAX INTEGER
    MAX-ACCESS read-write
    STATUS current
    DESCRIPTION
	    "
			[FW:E2080.AC.1-Serial:5.10.0]
	    "
    ::= { serialFormat  1 }

serialFormatDataBit OBJECT-TYPE
    SYNTAX INTEGER
    MAX-ACCESS read-write
    STATUS current
    DESCRIPTION
	    "
			6,7,8 data bit
			[FW:E2080.AC.1-Serial:5.10.0]
	    "
    ::= { serialFormat  2 }

serialFormatParityBit OBJECT-TYPE
    SYNTAX INTEGER {none(1),odd(2),even(3),mark(4),space(5)}
    MAX-ACCESS read-write
    STATUS current
    DESCRIPTION
	    "

			[FW:E2080.AC.1-Serial:5.10.0]
	    "
    ::= { serialFormat  3 }

serialFormatStopBit OBJECT-TYPE
    SYNTAX INTEGER
    MAX-ACCESS read-write
    STATUS current
    DESCRIPTION
	    "
			1 or 2 stop bits
			[FW:E2080.AC.1-Serial:5.10.0]
	    "
    ::= { serialFormat  4 }

serialElectricalInterface OBJECT-TYPE
    SYNTAX INTEGER {rs232(1), rs422Master(2), rs422Slave(3), rs485NoEcho(4), rs485echo(5)}
    MAX-ACCESS read-write
    STATUS current
    DESCRIPTION
	    "
			Select electrical serial interface (RS232, RS422 master / slave, RS485 echo /no echo
			[FW:E2080.AC.1-Serial:5.10.0]
	    "
    ::= { serialFormat  5 }

-- ------------------------
-- +++ Serial triggers +++

--send trigger char count
sendTriggerCharCountEnable OBJECT-TYPE
    SYNTAX INTEGER {enable(2),disable(1)}
    MAX-ACCESS read-write
    STATUS current
    DESCRIPTION
	    "
		Enable / disable this sendtrigger

		[FW:E2080.AC.1-Serial:5.10.0]
	    "
    ::= { serialSendTriggerCharcount  1 }

sendTriggerCharCountValue OBJECT-TYPE
    SYNTAX INTEGER
    MAX-ACCESS read-write
    STATUS current
    DESCRIPTION
	    "
		number of chars required in the buffer before emission to the client application.

		[FW:E2080.AC.1-Serial:5.10.0]
	    "
    ::= { serialSendTriggerCharcount  2 }

--send trigger Frame delay

sendTriggerFrameDelayEnable OBJECT-TYPE
    SYNTAX INTEGER {enable(2),disable(1)}
    MAX-ACCESS read-write
    STATUS current
    DESCRIPTION
	    "
		Enable / disable this sendtrigger

		[FW:E2080.AC.1-Serial:5.10.0]
	    "
    ::= { serialSendTriggerFrameDelay  1 }

sendTriggerFrameDelayValue OBJECT-TYPE
    SYNTAX INTEGER
    MAX-ACCESS read-write
    STATUS current
    DESCRIPTION
	    "
		delay between char reception and emission to the client application.

		[FW:E2080.AC.1-Serial:5.10.0]
	    "
    ::= { serialSendTriggerFrameDelay  2 }

sendTriggerFrameDelayUnit OBJECT-TYPE
    SYNTAX INTEGER {charTime(1),millisecond(2)}
    MAX-ACCESS read-write
    STATUS current
    DESCRIPTION
	    "
		Unit of send trigger

		[FW:E2080.AC.1-Serial:5.10.0]
	    "
    ::= { serialSendTriggerFrameDelay  3 }

-- Send trigger idle delay

sendTriggerIdleDelayEnable OBJECT-TYPE
    SYNTAX INTEGER {enable(2),disable(1)}
    MAX-ACCESS read-write
    STATUS current
    DESCRIPTION
	    "
		Enable / disable this sendtrigger

		[FW:E2080.AC.1-Serial:5.10.0]
	    "
    ::= { serialSendTriggerIdleDelay  1 }

sendTriggerIdleDelayValue OBJECT-TYPE
    SYNTAX INTEGER
    MAX-ACCESS read-write
    STATUS current
    DESCRIPTION
	    "
		delay between last char reception and emission to the client application

		[FW:E2080.AC.1-Serial:5.10.0]
	    "
    ::= { serialSendTriggerIdleDelay  2 }

sendTriggerIdleDelayUnit OBJECT-TYPE
    SYNTAX INTEGER {charTime(1),millisecond(2)}
    MAX-ACCESS read-write
    STATUS current
    DESCRIPTION
	    "
		Unit

		[FW:E2080.AC.1-Serial:5.10.0]
	    "
    ::= { serialSendTriggerIdleDelay  3 }


-- Serial services

serialServicetype OBJECT-TYPE
    SYNTAX INTEGER {virtualcom(1), modbusTcpSlave(2),modbusTcpMaster(3),tcpRawPortServer(4),tcpRawPortClient(5),udpRawPortServer(6),serialServiceInvalid(7)}
    MAX-ACCESS read-write
    STATUS current
    DESCRIPTION
	    "
			Define the type of service provided to the remote stations
			[FW:E2080.AC.1-Serial:5.10.0]
	    "
    ::= { serialInterface  1 }

--***********************
-- Serial interface Virtual port com (VIP)
--***********************
-- Serial interface ModbuSlave

modbusSlaveFormat OBJECT-TYPE
    SYNTAX INTEGER {ascii(1),rtu(2)}
    MAX-ACCESS read-write
    STATUS current
    DESCRIPTION
	    "
			[FW:E2080.AC.1-Serial:5.10.0]
	    "
    ::= { serialServiceModbusSlave  1 }

modbusSlaveSerialTransactionTimeout OBJECT-TYPE
    SYNTAX INTEGER
    MAX-ACCESS read-write
    STATUS current
    DESCRIPTION
	    "
			[FW:E2080.AC.1-Serial:5.10.0]
	    "
    ::= { serialServiceModbusSlave  2 }

-- Tcp raw port server

--Extra configuration for serial port

trsExtraConfigDTR OBJECT-TYPE
    SYNTAX INTEGER {default(1), tcpConnected(2), inputFlow(4), low(5), high(6)}
    MAX-ACCESS read-write
    STATUS current
    DESCRIPTION
	    "
			[FW:E2080.AC.1-Serial:5.10.0]
	    "
    ::= { tcpRawServerSerialExtraConfig  1 }

trsExtraConfigRTS OBJECT-TYPE
    SYNTAX INTEGER {default(1), modem(2), inputFlow(4), low(5), high(6)}
    MAX-ACCESS read-write
    STATUS current
    DESCRIPTION
	    "
			[FW:E2080.AC.1-Serial:5.10.0]
	    "
    ::= { tcpRawServerSerialExtraConfig  2 }

trsExtraConfigDSR OBJECT-TYPE
    SYNTAX INTEGER {default(1), acceptCall(2)}
    MAX-ACCESS read-write
    STATUS current
    DESCRIPTION
	    "
			[FW:E2080.AC.1-Serial:5.10.0]
	    "
    ::= { tcpRawServerSerialExtraConfig  3 }

trsExtraConfigCTS OBJECT-TYPE
    SYNTAX INTEGER {ignore(1), outputFlow(4)}
    MAX-ACCESS read-write
    STATUS current
    DESCRIPTION
	    "
			[FW:E2080.AC.1-Serial:5.10.0]
	    "
    ::= { tcpRawServerSerialExtraConfig  4 }

trsExtraConfigDCD OBJECT-TYPE
    SYNTAX INTEGER {ignore(1), rxData(2)}
    MAX-ACCESS read-write
    STATUS current
    DESCRIPTION
	    "
			[FW:E2080.AC.1-Serial:5.10.0]
	    "
    ::= { tcpRawServerSerialExtraConfig  5 }

trsExtraConfigXonXoff OBJECT-TYPE
    SYNTAX INTEGER {ignore(1), flowControl(7)}
    MAX-ACCESS read-write
    STATUS current
    DESCRIPTION
	    "
			[FW:E2080.AC.1-Serial:5.10.0]
	    "
    ::= { tcpRawServerSerialExtraConfig  6 }

-- **********************
-- udp raw port server
udpRawServerRemoteIP OBJECT-TYPE
    SYNTAX IpAddress
    MAX-ACCESS read-write
    STATUS current
    DESCRIPTION
	    "
			IP address of the remote network device, to which we send data. Using IP address 255.255.255.255 allows multidrop communication
			[FW:E2080.AC.1-Serial:5.10.0]
	    "
    ::= { serialServiceUdpRawPortServer  2}

udpRawServerRemotePort OBJECT-TYPE
    SYNTAX INTEGER
    MAX-ACCESS read-write
    STATUS current
    DESCRIPTION
	    "
			UDP port of the remote network device, used as a destination UDP port when we send data to remote devices on the network. If 0, local port is used.
			[FW:E2080.AC.1-Serial:5.10.0]
	    "
    ::= { serialServiceUdpRawPortServer  3}

udpRawServerLocalPort OBJECT-TYPE
    SYNTAX INTEGER
    MAX-ACCESS read-write
    STATUS current
    DESCRIPTION
	    "
			Our receiving UDP port (remote devices on the network use this destination to send us data)
			[FW:E2080.AC.1-Serial:5.10.0]
	    "
    ::= { serialServiceUdpRawPortServer  4}

ursExtraConfigDTR OBJECT-TYPE
    SYNTAX INTEGER {default(1), low(5), high(6)}
    MAX-ACCESS read-write
    STATUS current
    DESCRIPTION
	    "
			[FW:E2080.AC.1-Serial:5.10.0]
	    "
    ::= { udpRawServerSerialExtraConfig  1 }

ursExtraConfigRTS OBJECT-TYPE
    SYNTAX INTEGER {default(1), modem(2), inputFlow(4), low(5), high(6)}
    MAX-ACCESS read-write
    STATUS current
    DESCRIPTION
	    "
			[FW:E2080.AC.1-Serial:5.10.0]
	    "
    ::= { udpRawServerSerialExtraConfig  2 }

ursExtraConfigCTS OBJECT-TYPE
    SYNTAX INTEGER {ignore(1), outputFlow(4)}
    MAX-ACCESS read-write
    STATUS current
    DESCRIPTION
	    "
			[FW:E2080.AC.1-Serial:5.10.0]
	    "
    ::= { udpRawServerSerialExtraConfig  3 }

ursExtraConfigXonXoff OBJECT-TYPE
    SYNTAX INTEGER {ignore(1), flowControl(7)}
    MAX-ACCESS read-write
    STATUS current
    DESCRIPTION
	    "
			[FW:E2080.AC.1-Serial:5.10.0]
	    "
    ::= { udpRawServerSerialExtraConfig  4 }

-- modbus master
-- modbus master serial format

modbusMasterFormat OBJECT-TYPE
    SYNTAX INTEGER {ascii(1),rtu(2)}
    MAX-ACCESS read-write
    STATUS current
    DESCRIPTION
	    "
			[FW:E2080.AC.1-Serial:5.10.0]
	    "
    ::= { serialServiceModbusMaster  1 }

modbusMasterTransactionTimeout OBJECT-TYPE
    SYNTAX INTEGER
    MAX-ACCESS read-write
    STATUS current
    DESCRIPTION
	    "
			If the MODBUS/TCP slave device does not respond in the given time, an error response will be sent to the serial master.
			[FW:E2080.AC.1-Serial:5.10.0]
	    "
    ::= { serialServiceModbusMaster  2 }

mmForwardingTable-Rule1-FirstLocalAddr OBJECT-TYPE
    SYNTAX INTEGER
    MAX-ACCESS read-write
    STATUS current
    DESCRIPTION
	    "
			First MODBUS serial address (local)
			[FW:E2080.AC.1-Serial:5.10.0]
	    "
    ::= { modbusMasterForwardingTable-Rule1  1 }

mmForwardingTable-Rule1-LastLocalAddr OBJECT-TYPE
    SYNTAX INTEGER
    MAX-ACCESS read-write
    STATUS current
    DESCRIPTION
	    "
			Last MODBUS serial address (local)
			[FW:E2080.AC.1-Serial:5.10.0]
	    "
    ::= { modbusMasterForwardingTable-Rule1  2 }

mmForwardingTable-Rule1-FirstRemoteAddr OBJECT-TYPE
    SYNTAX INTEGER
    MAX-ACCESS read-write
    STATUS current
    DESCRIPTION
	    "
			First MODBUS TCP ID field (remote serial address)
			[FW:E2080.AC.1-Serial:5.10.0]
	    "
    ::= { modbusMasterForwardingTable-Rule1  3 }

mmForwardingTable-Rule1-SlaveIpAddrIncrement OBJECT-TYPE
    SYNTAX INTEGER {fixed(1),variable(2)}
    MAX-ACCESS read-write
    STATUS current
    DESCRIPTION
	    "
			1 = last byte of IP address fixed
			2 = last byte of IP address variable
			[FW:E2080.AC.1-Serial:5.10.0]
	    "
    ::= { modbusMasterForwardingTable-Rule1  4 }

mmForwardingTable-Rule1-SlaveIpAddr OBJECT-TYPE
    SYNTAX IpAddress
    MAX-ACCESS read-write
    STATUS current
    DESCRIPTION
	    "
			[FW:E2080.AC.1-Serial:5.10.0]
	    "
    ::= { modbusMasterForwardingTable-Rule1  5 }


mmForwardingTable-Rule2-FirstLocalAddr OBJECT-TYPE
    SYNTAX INTEGER
    MAX-ACCESS read-write
    STATUS current
    DESCRIPTION
	    "
			First MODBUS serial address (local)
			[FW:E2080.AC.1-Serial:5.10.0]
	    "
    ::= { modbusMasterForwardingTable-Rule2  1 }

mmForwardingTable-Rule2-LastLocalAddr OBJECT-TYPE
    SYNTAX INTEGER
    MAX-ACCESS read-write
    STATUS current
    DESCRIPTION
	    "
			Last MODBUS serial address (local)
			[FW:E2080.AC.1-Serial:5.10.0]
	    "
    ::= { modbusMasterForwardingTable-Rule2  2 }

mmForwardingTable-Rule2-FirstRemoteAddr OBJECT-TYPE
    SYNTAX INTEGER
    MAX-ACCESS read-write
    STATUS current
    DESCRIPTION
	    "
			First MODBUS TCP ID field (remote serial address)
			[FW:E2080.AC.1-Serial:5.10.0]
	    "
    ::= { modbusMasterForwardingTable-Rule2  3 }

mmForwardingTable-Rule2-SlaveIpAddrIncrement OBJECT-TYPE
    SYNTAX INTEGER {fixed(1),variable(2)}
    MAX-ACCESS read-write
    STATUS current
    DESCRIPTION
	    "
			1 = last byte of IP address fixed
			2 = last byte of IP address variable
			[FW:E2080.AC.1-Serial:5.10.0]
	    "
    ::= { modbusMasterForwardingTable-Rule2  4 }

mmForwardingTable-Rule2-SlaveIpAddr OBJECT-TYPE
    SYNTAX IpAddress
    MAX-ACCESS read-write
    STATUS current
    DESCRIPTION
	    "
			[FW:E2080.AC.1-Serial:5.10.0]
	    "
    ::= { modbusMasterForwardingTable-Rule2  5 }

mmForwardingTable-Rule3-FirstLocalAddr OBJECT-TYPE
    SYNTAX INTEGER
    MAX-ACCESS read-write
    STATUS current
    DESCRIPTION
	    "
			First MODBUS serial address (local)
			[FW:E2080.AC.1-Serial:5.10.0]
	    "
    ::= { modbusMasterForwardingTable-Rule3  1 }

mmForwardingTable-Rule3-LastLocalAddr OBJECT-TYPE
    SYNTAX INTEGER
    MAX-ACCESS read-write
    STATUS current
    DESCRIPTION
	    "
			Last MODBUS serial address (local)
			[FW:E2080.AC.1-Serial:5.10.0]
	    "
    ::= { modbusMasterForwardingTable-Rule3  2 }

mmForwardingTable-Rule3-FirstRemoteAddr OBJECT-TYPE
    SYNTAX INTEGER
    MAX-ACCESS read-write
    STATUS current
    DESCRIPTION
	    "
			First MODBUS TCP ID field (remote serial address)
			[FW:E2080.AC.1-Serial:5.10.0]
	    "
    ::= { modbusMasterForwardingTable-Rule3  3 }

mmForwardingTable-Rule3-SlaveIpAddrIncrement OBJECT-TYPE
    SYNTAX INTEGER {fixed(1),variable(2)}
    MAX-ACCESS read-write
    STATUS current
    DESCRIPTION
	    "
			1 = last byte of IP address fixed
			2 = last byte of IP address variable
			[FW:E2080.AC.1-Serial:5.10.0]
	    "
    ::= { modbusMasterForwardingTable-Rule3  4 }

mmForwardingTable-Rule3-SlaveIpAddr OBJECT-TYPE
    SYNTAX IpAddress
    MAX-ACCESS read-write
    STATUS current
    DESCRIPTION
	    "
			[FW:E2080.AC.1-Serial:5.10.0]
	    "
    ::= { modbusMasterForwardingTable-Rule3  5 }

mmForwardingTable-Rule4-FirstLocalAddr OBJECT-TYPE
    SYNTAX INTEGER
    MAX-ACCESS read-write
    STATUS current
    DESCRIPTION
	    "
			First MODBUS serial address (local)
			[FW:E2080.AC.1-Serial:5.10.0]
	    "
    ::= { modbusMasterForwardingTable-Rule4  1 }

mmForwardingTable-Rule4-LastLocalAddr OBJECT-TYPE
    SYNTAX INTEGER
    MAX-ACCESS read-write
    STATUS current
    DESCRIPTION
	    "
			Last MODBUS serial address (local)
			[FW:E2080.AC.1-Serial:5.10.0]
	    "
    ::= { modbusMasterForwardingTable-Rule4  2 }

mmForwardingTable-Rule4-FirstRemoteAddr OBJECT-TYPE
    SYNTAX INTEGER
    MAX-ACCESS read-write
    STATUS current
    DESCRIPTION
	    "
			First MODBUS TCP ID field (remote serial address)
			[FW:E2080.AC.1-Serial:5.10.0]
	    "
    ::= { modbusMasterForwardingTable-Rule4  3 }

mmForwardingTable-Rule4-SlaveIpAddrIncrement OBJECT-TYPE
    SYNTAX INTEGER {fixed(1),variable(2)}
    MAX-ACCESS read-write
    STATUS current
    DESCRIPTION
	    "
			1 = last byte of IP address fixed
			2 = last byte of IP address variable
			[FW:E2080.AC.1-Serial:5.10.0]
	    "
    ::= { modbusMasterForwardingTable-Rule4  4 }

mmForwardingTable-Rule4-SlaveIpAddr OBJECT-TYPE
    SYNTAX IpAddress
    MAX-ACCESS read-write
    STATUS current
    DESCRIPTION
	    "
			[FW:E2080.AC.1-Serial:5.10.0]
	    "
    ::= { modbusMasterForwardingTable-Rule4  5 }

mmForwardingTable-Rule5-FirstLocalAddr OBJECT-TYPE
    SYNTAX INTEGER
    MAX-ACCESS read-write
    STATUS current
    DESCRIPTION
	    "
			First MODBUS serial address (local)
			[FW:E2080.AC.1-Serial:5.10.0]
	    "
    ::= { modbusMasterForwardingTable-Rule5  1 }

mmForwardingTable-Rule5-LastLocalAddr OBJECT-TYPE
    SYNTAX INTEGER
    MAX-ACCESS read-write
    STATUS current
    DESCRIPTION
	    "
			Last MODBUS serial address (local)
			[FW:E2080.AC.1-Serial:5.10.0]
	    "
    ::= { modbusMasterForwardingTable-Rule5  2 }

mmForwardingTable-Rule5-FirstRemoteAddr OBJECT-TYPE
    SYNTAX INTEGER
    MAX-ACCESS read-write
    STATUS current
    DESCRIPTION
	    "
			First MODBUS TCP ID field (remote serial address)
			[FW:E2080.AC.1-Serial:5.10.0]
	    "
    ::= { modbusMasterForwardingTable-Rule5  3 }

mmForwardingTable-Rule5-SlaveIpAddrIncrement OBJECT-TYPE
    SYNTAX INTEGER {fixed(1),variable(2)}
    MAX-ACCESS read-write
    STATUS current
    DESCRIPTION
	    "
			1 = last byte of IP address fixed
			2 = last byte of IP address variable
			[FW:E2080.AC.1-Serial:5.10.0]
	    "
    ::= { modbusMasterForwardingTable-Rule5  4 }

mmForwardingTable-Rule5-SlaveIpAddr OBJECT-TYPE
    SYNTAX IpAddress
    MAX-ACCESS read-write
    STATUS current
    DESCRIPTION
	    "
			[FW:E2080.AC.1-Serial:5.10.0]
	    "
    ::= { modbusMasterForwardingTable-Rule5  5 }

mmForwardingTable-Rule6-FirstLocalAddr OBJECT-TYPE
    SYNTAX INTEGER
    MAX-ACCESS read-write
    STATUS current
    DESCRIPTION
	    "
			First MODBUS serial address (local)
			[FW:E2080.AC.1-Serial:5.10.0]
	    "
    ::= { modbusMasterForwardingTable-Rule6  1 }

mmForwardingTable-Rule6-LastLocalAddr OBJECT-TYPE
    SYNTAX INTEGER
    MAX-ACCESS read-write
    STATUS current
    DESCRIPTION
	    "
			Last MODBUS serial address (local)
			[FW:E2080.AC.1-Serial:5.10.0]
	    "
    ::= { modbusMasterForwardingTable-Rule6  2 }

mmForwardingTable-Rule6-FirstRemoteAddr OBJECT-TYPE
    SYNTAX INTEGER
    MAX-ACCESS read-write
    STATUS current
    DESCRIPTION
	    "
			First MODBUS TCP ID field (remote serial address)
			[FW:E2080.AC.1-Serial:5.10.0]
	    "
    ::= { modbusMasterForwardingTable-Rule6  3 }

mmForwardingTable-Rule6-SlaveIpAddrIncrement OBJECT-TYPE
    SYNTAX INTEGER {fixed(1),variable(2)}
    MAX-ACCESS read-write
    STATUS current
    DESCRIPTION
	    "
			1 = last byte of IP address fixed
			2 = last byte of IP address variable
			[FW:E2080.AC.1-Serial:5.10.0]
	    "
    ::= { modbusMasterForwardingTable-Rule6  4 }

mmForwardingTable-Rule6-SlaveIpAddr OBJECT-TYPE
    SYNTAX IpAddress
    MAX-ACCESS read-write
    STATUS current
    DESCRIPTION
	    "
			[FW:E2080.AC.1-Serial:5.10.0]
	    "
    ::= { modbusMasterForwardingTable-Rule6  5 }

mmForwardingTable-Rule7-FirstLocalAddr OBJECT-TYPE
    SYNTAX INTEGER
    MAX-ACCESS read-write
    STATUS current
    DESCRIPTION
	    "
			First MODBUS serial address (local)
			[FW:E2080.AC.1-Serial:5.10.0]
	    "
    ::= { modbusMasterForwardingTable-Rule7  1 }

mmForwardingTable-Rule7-LastLocalAddr OBJECT-TYPE
    SYNTAX INTEGER
    MAX-ACCESS read-write
    STATUS current
    DESCRIPTION
	    "
			Last MODBUS serial address (local)
			[FW:E2080.AC.1-Serial:5.10.0]
	    "
    ::= { modbusMasterForwardingTable-Rule7  2 }

mmForwardingTable-Rule7-FirstRemoteAddr OBJECT-TYPE
    SYNTAX INTEGER
    MAX-ACCESS read-write
    STATUS current
    DESCRIPTION
	    "
			First MODBUS TCP ID field (remote serial address)
			[FW:E2080.AC.1-Serial:5.10.0]
	    "
    ::= { modbusMasterForwardingTable-Rule7  3 }

mmForwardingTable-Rule7-SlaveIpAddrIncrement OBJECT-TYPE
    SYNTAX INTEGER {fixed(1),variable(2)}
    MAX-ACCESS read-write
    STATUS current
    DESCRIPTION
	    "
			1 = last byte of IP address fixed
			2 = last byte of IP address variable
			[FW:E2080.AC.1-Serial:5.10.0]
	    "
    ::= { modbusMasterForwardingTable-Rule7  4 }

mmForwardingTable-Rule7-SlaveIpAddr OBJECT-TYPE
    SYNTAX IpAddress
    MAX-ACCESS read-write
    STATUS current
    DESCRIPTION
	    "
			[FW:E2080.AC.1-Serial:5.10.0]
	    "
    ::= { modbusMasterForwardingTable-Rule7  5 }

mmForwardingTable-Rule8-FirstLocalAddr OBJECT-TYPE
    SYNTAX INTEGER
    MAX-ACCESS read-write
    STATUS current
    DESCRIPTION
	    "
			First MODBUS serial address (local)
			[FW:E2080.AC.1-Serial:5.10.0]
	    "
    ::= { modbusMasterForwardingTable-Rule8  1 }

mmForwardingTable-Rule8-LastLocalAddr OBJECT-TYPE
    SYNTAX INTEGER
    MAX-ACCESS read-write
    STATUS current
    DESCRIPTION
	    "
			Last MODBUS serial address (local)
			[FW:E2080.AC.1-Serial:5.10.0]
	    "
    ::= { modbusMasterForwardingTable-Rule8  2 }

mmForwardingTable-Rule8-FirstRemoteAddr OBJECT-TYPE
    SYNTAX INTEGER
    MAX-ACCESS read-write
    STATUS current
    DESCRIPTION
	    "
			First MODBUS TCP ID field (remote serial address)
			[FW:E2080.AC.1-Serial:5.10.0]
	    "
    ::= { modbusMasterForwardingTable-Rule8  3 }

mmForwardingTable-Rule8-SlaveIpAddrIncrement OBJECT-TYPE
    SYNTAX INTEGER {fixed(1),variable(2)}
    MAX-ACCESS read-write
    STATUS current
    DESCRIPTION
	    "
			1 = last byte of IP address fixed
			2 = last byte of IP address variable
			[FW:E2080.AC.1-Serial:5.10.0]
	    "
    ::= { modbusMasterForwardingTable-Rule8  4 }

mmForwardingTable-Rule8-SlaveIpAddr OBJECT-TYPE
    SYNTAX IpAddress
    MAX-ACCESS read-write
    STATUS current
    DESCRIPTION
	    "
			[FW:E2080.AC.1-Serial:5.10.0]
	    "
    ::= { modbusMasterForwardingTable-Rule8  5 }

-- raw Tcp client
--Extra configuration for serial port

trcExtraConfigDTR OBJECT-TYPE
    SYNTAX INTEGER {default(1), low(5), high(6)}
    MAX-ACCESS read-write
    STATUS current
    DESCRIPTION
	    "
			[FW:E2080.AC.1-Serial:5.10.0]
	    "
    ::= { tcpRawClientSerialExtraConfig  1 }

trcExtraConfigRTS OBJECT-TYPE
    SYNTAX INTEGER {default(1), modem(2), inputFlow(4), low(5), high(6)}
    MAX-ACCESS read-write
    STATUS current
    DESCRIPTION
	    "
			[FW:E2080.AC.1-Serial:5.10.0]
	    "
    ::= { tcpRawClientSerialExtraConfig  2 }



trcExtraConfigCTS OBJECT-TYPE
    SYNTAX INTEGER {ignore(1), outputFlow(4)}
    MAX-ACCESS read-write
    STATUS current
    DESCRIPTION
	    "
			[FW:E2080.AC.1-Serial:5.10.0]
	    "
    ::= { tcpRawClientSerialExtraConfig  4 }

trcExtraConfigDCD OBJECT-TYPE
    SYNTAX INTEGER {ignore(1), rxData(2)}
    MAX-ACCESS read-write
    STATUS current
    DESCRIPTION
	    "
			[FW:E2080.AC.1-Serial:5.10.0]
	    "
    ::= { tcpRawClientSerialExtraConfig  5 }

trcExtraConfigXonXoff OBJECT-TYPE
    SYNTAX INTEGER {ignore(1), flowControl(7)}
    MAX-ACCESS read-write
    STATUS current
    DESCRIPTION
	    "
			[FW:E2080.AC.1-Serial:5.10.0]
	    "
    ::= { tcpRawClientSerialExtraConfig  6 }

tcpRawClientConnectionTimeout OBJECT-TYPE
    SYNTAX INTEGER
    MAX-ACCESS read-write
    STATUS current
    DESCRIPTION
	    "
			How long before we give up trying to call a server. 0 means indefinitely.
			[FW:E2080.AC.1-Serial:5.10.0]
	    "
    ::= { serialServiceTcpRawPortClient  4 }

tcpRawClientPollPeriode OBJECT-TYPE
    SYNTAX INTEGER
    MAX-ACCESS read-write
    STATUS current
    DESCRIPTION
	    "
			How long we wait between two scans of the servers list (in case no server is available).
			[FW:E2080.AC.1-Serial:5.10.0]
	    "
    ::= { serialServiceTcpRawPortClient  5 }

tcpRawClientDSRUse OBJECT-TYPE
    SYNTAX INTEGER {notUsed(1),graceful(2),fast(3)}
    MAX-ACCESS read-write
    STATUS current
    DESCRIPTION
	    "
			How the DSR pin causes server calls and connection terminations
			[FW:E2080.AC.1-Serial:5.10.0]
	    "
    ::= { serialServiceTcpRawPortClient  6 }

-- server table
tcpRawClienServer1-IpAddress OBJECT-TYPE
    SYNTAX IpAddress
    MAX-ACCESS read-write
    STATUS current
    DESCRIPTION
	    "
			[FW:E2080.AC.1-Serial:5.10.0]
	    "
    ::= { tcpRawClientServer1  1 }

tcpRawclientServer1-TcpPort OBJECT-TYPE
    SYNTAX INTEGER
    MAX-ACCESS read-write
    STATUS current
    DESCRIPTION
	    "
			[FW:E2080.AC.1-Serial:5.10.0]
	    "
    ::= { tcpRawClientServer1  2 }

tcpRawclientServer2-IpAddress OBJECT-TYPE
    SYNTAX IpAddress
    MAX-ACCESS read-write
    STATUS current
    DESCRIPTION
	    "
			[FW:E2080.AC.1-Serial:5.10.0]
	    "
    ::= { tcpRawClientServer2  1 }

tcpRawclientServer2-TcpPort OBJECT-TYPE
    SYNTAX INTEGER
    MAX-ACCESS read-write
    STATUS current
    DESCRIPTION
	    "
			[FW:E2080.AC.1-Serial:5.10.0]
	    "
    ::= { tcpRawClientServer2  2 }

tcpRawclientServer3-IpAddress OBJECT-TYPE
    SYNTAX IpAddress
    MAX-ACCESS read-write
    STATUS current
    DESCRIPTION
	    "
			[FW:E2080.AC.1-Serial:5.10.0]
	    "
    ::= { tcpRawClientServer3  1 }

tcpRawclientServer3-TcpPort OBJECT-TYPE
    SYNTAX INTEGER
    MAX-ACCESS read-write
    STATUS current
    DESCRIPTION
	    "
			[FW:E2080.AC.1-Serial:5.10.0]
	    "
    ::= { tcpRawClientServer3  2 }

tcpRawclientServer4-IpAddress OBJECT-TYPE
    SYNTAX IpAddress
    MAX-ACCESS read-write
    STATUS current
    DESCRIPTION
	    "
			[FW:E2080.AC.1-Serial:5.10.0]
	    "
    ::= { tcpRawClientServer4  1 }

tcpRawclientServer4-TcpPort OBJECT-TYPE
    SYNTAX INTEGER
    MAX-ACCESS read-write
    STATUS current
    DESCRIPTION
	    "
			[FW:E2080.AC.1-Serial:5.10.0]
	    "
    ::= { tcpRawClientServer4  2 }

tcpRawclientServer5-IpAddress OBJECT-TYPE
    SYNTAX IpAddress
    MAX-ACCESS read-write
    STATUS current
    DESCRIPTION
	    "
			[FW:E2080.AC.1-Serial:5.10.0]
	    "
    ::= { tcpRawClientServer5  1 }

tcpRawclientServer5-TcpPort OBJECT-TYPE
    SYNTAX INTEGER
    MAX-ACCESS read-write
    STATUS current
    DESCRIPTION
	    "
			[FW:E2080.AC.1-Serial:5.10.0]
	    "
    ::= { tcpRawClientServer5  2 }

tcpRawclientServer6-IpAddress OBJECT-TYPE
    SYNTAX IpAddress
    MAX-ACCESS read-write
    STATUS current
    DESCRIPTION
	    "
			[FW:E2080.AC.1-Serial:5.10.0]
	    "
    ::= { tcpRawClientServer6  1 }

tcpRawclientServer6-TcpPort OBJECT-TYPE
    SYNTAX INTEGER
    MAX-ACCESS read-write
    STATUS current
    DESCRIPTION
	    "
			[FW:E2080.AC.1-Serial:5.10.0]
	    "
    ::= { tcpRawClientServer6  2 }

tcpRawclientServer7-IpAddress OBJECT-TYPE
    SYNTAX IpAddress
    MAX-ACCESS read-write
    STATUS current
    DESCRIPTION
	    "
			[FW:E2080.AC.1-Serial:5.10.0]
	    "
    ::= { tcpRawClientServer7  1 }

tcpRawclientServer7-TcpPort OBJECT-TYPE
    SYNTAX INTEGER
    MAX-ACCESS read-write
    STATUS current
    DESCRIPTION
	    "
			[FW:E2080.AC.1-Serial:5.10.0]
	    "
    ::= { tcpRawClientServer7  2 }

tcpRawclientServer8-IpAddress OBJECT-TYPE
    SYNTAX IpAddress
    MAX-ACCESS read-write
    STATUS current
    DESCRIPTION
	    "
			[FW:E2080.AC.1-Serial:5.10.0]
	    "
    ::= { tcpRawClientServer8  1 }

tcpRawclientServer8-TcpPort OBJECT-TYPE
    SYNTAX INTEGER
    MAX-ACCESS read-write
    STATUS current
    DESCRIPTION
	    "
			[FW:E2080.AC.1-Serial:5.10.0]
	    "
    ::= { tcpRawClientServer8  2 }

-- =========================================
-- networkStatus (current operational state)
--

-- Tables - IP subnets

statusIpSubnetTable OBJECT-TYPE
	SYNTAX SEQUENCE OF StatusIpSubnetEntry
	MAX-ACCESS not-accessible STATUS current
	DESCRIPTION "A table that contains information of logical networks (level 3).
   		    [FW:E2148.AC.1:3.14.0.1]"
	::= { networkStatus 1 }

statusIpSubnetEntry OBJECT-TYPE
	SYNTAX StatusIpSubnetEntry
	MAX-ACCESS not-accessible STATUS current
	DESCRIPTION "A table that contains network information."
	INDEX { statusIpSubnetIndex }
	::= { statusIpSubnetTable 1 }

StatusIpSubnetEntry ::=
	SEQUENCE {
		statusIpSubnetIndex INTEGER
		,statusIpSubnetName NetifName
		,statusIpSubnetLabel DisplayString
		,statusIpSubnetIfIndex INTEGER
		,statusIpSubnetAddrMode INTEGER
		,statusIpSubnetIPv4Addr IpAddress
		,statusIpSubnetIPv4Mask IpAddress
		,statusIpSubnetDNS DisplayString
		,statusIpSubnetMember DisplayString
		,statusIpSubnetMemberIndex DisplayString
	}
	statusIpSubnetIndex OBJECT-TYPE
		SYNTAX INTEGER MAX-ACCESS read-only STATUS current
		DESCRIPTION "Network index"
		::= { statusIpSubnetEntry 1 }

	statusIpSubnetName OBJECT-TYPE
		SYNTAX NetifName MAX-ACCESS read-only STATUS current
		DESCRIPTION "Network interface name"
		::= { statusIpSubnetEntry 2 }

	statusIpSubnetLabel OBJECT-TYPE
		SYNTAX DisplayString MAX-ACCESS read-only STATUS current
		DESCRIPTION "Network friendly name"
		::= { statusIpSubnetEntry 3 }

	statusIpSubnetIfIndex OBJECT-TYPE
		SYNTAX INTEGER MAX-ACCESS read-only STATUS current
		DESCRIPTION "Network kernel index"
		::= { statusIpSubnetEntry 4 }

	statusIpSubnetAddrMode OBJECT-TYPE
		SYNTAX INTEGER {static(1),dhcp(2),none(3),vrrp(4)}
		MAX-ACCESS read-only STATUS current
		DESCRIPTION "Ip address protocol of this network"
		::= { statusIpSubnetEntry 5 }

	statusIpSubnetIPv4Addr OBJECT-TYPE
		SYNTAX IpAddress MAX-ACCESS read-only STATUS current
		DESCRIPTION "Current IPv4 address of this network"
		::= { statusIpSubnetEntry 6 }

	statusIpSubnetIPv4Mask OBJECT-TYPE
		SYNTAX IpAddress MAX-ACCESS read-only STATUS current
		DESCRIPTION "Current IPv4 subnet mask of this network"
		::= { statusIpSubnetEntry 7 }

	statusIpSubnetDNS OBJECT-TYPE
		SYNTAX DisplayString MAX-ACCESS read-only STATUS current
		DESCRIPTION "Space-separated list of DNS IP addresses"
		::= { statusIpSubnetEntry 8 }

	statusIpSubnetMember OBJECT-TYPE
		SYNTAX DisplayString MAX-ACCESS read-only STATUS current
		DESCRIPTION "Space-separated list that contains name of interfaces related to this network"
		::= { statusIpSubnetEntry 9 }

	statusIpSubnetMemberIndex OBJECT-TYPE
		SYNTAX DisplayString MAX-ACCESS read-only STATUS current
		DESCRIPTION "Space-separated list that contains kernel index of interfaces related to this network"
		::= { statusIpSubnetEntry 10 }

--Tables - Wi-Fi SSIDs
statusIfWlanTable OBJECT-TYPE
	SYNTAX SEQUENCE OF StatusIfWlanEntry
	MAX-ACCESS not-accessible
	STATUS current
	DESCRIPTION
		"List of Wi-Fi service sets (ESSID, ISSID)
		with an IP address
		[FW:E2148.AC.1:2.8.0.1]"
	::= { networkStatus 2 }

statusIfWlanEntry OBJECT-TYPE
	SYNTAX StatusIfWlanEntry
	MAX-ACCESS not-accessible
	STATUS current
	DESCRIPTION
		"Details about a Wi-Fi service set"
	INDEX { statusIfWlanIndex }
	::= { statusIfWlanTable 1 }

-- Tables - radio devices
statusPhyWifiTable OBJECT-TYPE
	SYNTAX SEQUENCE OF StatusPhyWifiEntry
	MAX-ACCESS not-accessible
	STATUS current
	DESCRIPTION "This table contains information about Wi-Fi adapters.
		[FW:E2148.AC.1:2.8.0.1]"
	::= { networkStatus 3 }

statusPhyWifiEntry OBJECT-TYPE
	SYNTAX StatusPhyWifiEntry
	MAX-ACCESS not-accessible
	STATUS current
	DESCRIPTION
		"Details about a Wi-Fi service set"
	INDEX { statusPhyWifiIndex }
	::= { statusPhyWifiTable 1 }

-- Tables - Wifi scan
statusPhyWifiScanTable OBJECT-TYPE
	SYNTAX SEQUENCE OF StatusPhyWifiScanEntry
	MAX-ACCESS not-accessible
	STATUS current
	DESCRIPTION
		"List of Wi-Fi access points devices around
		[FW:E2148.AC.1:2.8.0.1]"
	::= { networkStatus 4 }

statusPhyWifiScanEntry OBJECT-TYPE
	SYNTAX StatusPhyWifiScanEntry
	MAX-ACCESS not-accessible
	STATUS current
	DESCRIPTION
		"Details about a Wi-Fi access point"
	INDEX { statusPhyWifiScanTableIndex }
	::= { statusPhyWifiScanTable 1 }

-- Scan launch OID
statusPhyWifiScanTableStart OBJECT-TYPE
	SYNTAX INTEGER
	MAX-ACCESS read-write
	STATUS current
	DESCRIPTION
		"Write (any value) to start a scan. Poll the statusPhyWifiScanUpdateTbl
		 OID to know the status of the current scan : inprogress or available
		[FW:E2148.AC.1:2.8.0.1]"
	::= { networkStatus 5 }

-- Scan launch OID
statusPhyWifiScanUpdateTbl OBJECT-TYPE
	SYNTAX OCTET STRING (SIZE(0..32))
	MAX-ACCESS read-write
	STATUS current
	DESCRIPTION
		"Returns inprogress if current scan isn't finished yet.
		 Returns available if the current scan results are available. In this
		 case, the ScanTable will be updated with the new values.
		 An ESSID can be given to filter the scan result. In this case, the
		 device with an ESSID different than the given filter will be excluded.
		 This filter is reseted by a writting the statusPhyWifiScanTableStart OID.
		 Note that this OID have to be polled to know when the scan ends.
		[FW:E2148.AC.1:2.8.0.1]"
	::= { networkStatus 6 }

-- Elements in the Wi-Fi service sets status table

StatusIfWlanEntry ::=
    SEQUENCE {
		statusIfWlanIndex INTEGER,
		statusIfWlanSSID OCTET STRING,
		statusIfWlanMode INTEGER,
		statusIfWlanBand WifiFlavor,
		statusIfWlanChannel INTEGER,
		statusIfWlanFrequency INTEGER,
		statusIfWlanEnable INTEGER,
		statusIfWlanPhy INTEGER,
		statusIfWlanSecurityMode INTEGER,
		statusIfWlanWpaVersion INTEGER,
		statusIfWlanNPeers INTEGER,
		statusIfWlanQuality INTEGER,
		statusIfWlanBssid PhysAddress,
		statusIfWlanState INTEGER,
		statusIfStaFastBSSTransitionActivated DisableEnable,
		statusIfWlanBeaconSignalAvg INTEGER,
		statusIfWlanNoise INTEGER,
		statusIfWlanWpaCipher CipherTypes,
		statusIfWlanWpaPreSharedKey OCTET STRING,
		statusIfWlanName DisplayString,
		statusIfWlanIfIndex INTEGER
	}

statusIfWlanIndex OBJECT-TYPE
	SYNTAX INTEGER MAX-ACCESS read-only STATUS current
	DESCRIPTION "Wlan index"
	::= { statusIfWlanEntry 1 }

statusIfWlanSSID OBJECT-TYPE
	SYNTAX OCTET STRING(SIZE(0..32))
	MAX-ACCESS read-only STATUS current
	DESCRIPTION "SSID string"
	::= { statusIfWlanEntry 2 }

statusIfWlanMode OBJECT-TYPE
	SYNTAX INTEGER {
		undefined(0),
		infra-client(1),
		access-point(2),
		ad-hoc(3),
		monitor(5),
		ieee80211s(6),
		repeater(7),
		isolating-access-point(8)
		}
	MAX-ACCESS read-only STATUS current
	DESCRIPTION "STA role"
	::= { statusIfWlanEntry 3 }

statusIfWlanBand OBJECT-TYPE
	SYNTAX  WifiFlavor MAX-ACCESS read-only STATUS current
	DESCRIPTION "Wlan band/modulation type mix"
	::= { statusIfWlanEntry 4 }

statusIfWlanChannel OBJECT-TYPE
	SYNTAX INTEGER MAX-ACCESS read-only STATUS current
	DESCRIPTION "Wlan channel (frequency span index):
	-1 channel indicates that the product is searching for a channel"
	::= { statusIfWlanEntry 5 }

statusIfWlanFrequency OBJECT-TYPE
	SYNTAX INTEGER MAX-ACCESS read-only STATUS current
	DESCRIPTION "Radio frequency:
	0 frequency indicates that the product is searching for a radio frequency"
	::= { statusIfWlanEntry 6 }

statusIfWlanEnable OBJECT-TYPE
	SYNTAX DisableEnable
	MAX-ACCESS read-only STATUS current
	DESCRIPTION "Operational state"
	::= { statusIfWlanEntry 7 }

statusIfWlanPhy OBJECT-TYPE
	SYNTAX INTEGER
	MAX-ACCESS read-only STATUS current
	DESCRIPTION "PHY index for this wlan"
	::= { statusIfWlanEntry 8 }

statusIfWlanSecurityMode OBJECT-TYPE
	SYNTAX SecurityModes
	MAX-ACCESS read-only STATUS current
	DESCRIPTION "Security policy"
	::= { statusIfWlanEntry 9 }

statusIfWlanWpaVersion OBJECT-TYPE
	SYNTAX INTEGER
	MAX-ACCESS read-only STATUS current
	DESCRIPTION "WPA version (version 1 is deprecated)"
	::= { statusIfWlanEntry 10 }

statusIfWlanNPeers OBJECT-TYPE
	SYNTAX INTEGER
	MAX-ACCESS read-only STATUS current
	DESCRIPTION "Number of peer clients"
	::= { statusIfWlanEntry 11 }

statusIfWlanQuality OBJECT-TYPE
	SYNTAX INTEGER
	MAX-ACCESS read-only STATUS current
	DESCRIPTION "Radio link quality"
	::= { statusIfWlanEntry 12 }

statusIfWlanBssid OBJECT-TYPE
	SYNTAX PhysAddress
	MAX-ACCESS read-only STATUS current
	DESCRIPTION "BSSID"
	::= { statusIfWlanEntry 13 }

statusIfWlanState OBJECT-TYPE
	SYNTAX INTEGER {
			not-connected(0)
			,connected(9)
			}
	MAX-ACCESS read-only STATUS current
	DESCRIPTION "Connection state"
	::= { statusIfWlanEntry 14 }

statusIfStaFastBSSTransitionActivated OBJECT-TYPE
	SYNTAX DisableEnable
	MAX-ACCESS read-only STATUS current
	DESCRIPTION "802.11r support (dot11FastBSSTransitionActivated)"
	::= { statusIfWlanEntry 15 }

statusIfWlanBeaconSignalAvg OBJECT-TYPE
	SYNTAX INTEGER
	MAX-ACCESS read-only STATUS current
	DESCRIPTION "Signal level average in dBm of the last few beacons received
		     Before WaveOS V2.8.0.1, this OID gives the last beacon signal
		     After  WaveOS V2.8.0.1, this OID gives the avg of the last few beacons received"
	::= { statusIfWlanEntry 16 }

statusIfWlanNoise OBJECT-TYPE
	SYNTAX INTEGER
	MAX-ACCESS read-only STATUS current
	DESCRIPTION "Noise level in dBm"
	::= { statusIfWlanEntry 17 }

statusIfWlanWpaCipher OBJECT-TYPE
	SYNTAX CipherTypes
	MAX-ACCESS read-only STATUS current
	DESCRIPTION "WPA cipher"
	::= { statusIfWlanEntry 18 }

statusIfWlanWpaPreSharedKey OBJECT-TYPE
	SYNTAX OCTET STRING
	MAX-ACCESS read-only STATUS current
	DESCRIPTION "WPA PSK pre-shared key"
	::= { statusIfWlanEntry 19 }

statusIfWlanName OBJECT-TYPE
	SYNTAX DisplayString
	MAX-ACCESS read-only STATUS current
	DESCRIPTION "Wireless interface name
	[FW:E2148.AC.1:3.14.0.1]"
	::= { statusIfWlanEntry 20 }

statusIfWlanIfIndex OBJECT-TYPE
	SYNTAX INTEGER
	MAX-ACCESS read-only STATUS current
	DESCRIPTION "Wireless interface kernel index
	[FW:E2148.AC.1:3.14.0.1]"
	::= { statusIfWlanEntry 21 }

-- Elements in the radio cards status table

StatusPhyWifiEntry ::=
    SEQUENCE {
		statusPhyWifiIndex INTEGER
		,statusPhyWifiLabel DisplayString
		,statusPhyWifiEnable INTEGER
		,statusPhyWifiName NetifName
		,statusPhyWifiClusterMode OCTET STRING
		,statusPhyWifiClusterList OCTET STRING
		,statusPhyWifiClusterArgs OCTET STRING
		,statusPhyWifiMAC PhysAddress
		,statusPhyWifiWids INTEGER
--		,statusPhyWifiMaxScanSsid INTEGER
--		,statusPhyWifiRtsThreshold INTEGER
	}

	statusPhyWifiIndex OBJECT-TYPE
		SYNTAX INTEGER MAX-ACCESS read-only STATUS current
		DESCRIPTION "Radio device index"
		::= { statusPhyWifiEntry 1 }

	statusPhyWifiLabel OBJECT-TYPE
		SYNTAX DisplayString MAX-ACCESS read-only STATUS current
		DESCRIPTION "Friendly name"
		::= { statusPhyWifiEntry 2 }

	statusPhyWifiEnable OBJECT-TYPE
		SYNTAX DisableEnable MAX-ACCESS read-only STATUS current
		DESCRIPTION "Operational state"
		::= { statusPhyWifiEntry 3 }

	statusPhyWifiName OBJECT-TYPE
		SYNTAX NetifName MAX-ACCESS read-only STATUS current
		DESCRIPTION "Friendly name"
		::= { statusPhyWifiEntry 4 }

	statusPhyWifiClusterMode OBJECT-TYPE
		SYNTAX OCTET STRING(SIZE(0..16)) MAX-ACCESS read-only STATUS current
		DESCRIPTION "Cluster mode, empty for none, 'dualscan' for data/scan separation"
		::= { statusPhyWifiEntry 5 }

	statusPhyWifiClusterList OBJECT-TYPE
		SYNTAX OCTET STRING(SIZE(0..64)) MAX-ACCESS read-only STATUS current
		DESCRIPTION "List of device names in the cluster, e.g. 'radio0 radio1'"
		::= { statusPhyWifiEntry 6 }

	statusPhyWifiClusterArgs OBJECT-TYPE
		SYNTAX OCTET STRING(SIZE(0..64)) MAX-ACCESS read-only STATUS current
		DESCRIPTION "Cluster params for this device. For 'dualscan' mode,
				one device must be set to 'scan',
				the others in the cluster must be set to 'data'."
		::= { statusPhyWifiEntry 7 }

	statusPhyWifiMAC OBJECT-TYPE
		SYNTAX PhysAddress MAX-ACCESS read-only STATUS current
		DESCRIPTION "MAC address of the radio device
		[FW:E2148.AC.1:3.14.0.1]"
		::= { statusPhyWifiEntry 8 }

	statusPhyWifiWids OBJECT-TYPE
		SYNTAX INTEGER MAX-ACCESS read-only STATUS current
		DESCRIPTION "WIDS services state. 0: not started.
		1: currently monitoring for rogue APs.
		[FW:E2148.AC.1:4.16.0.1]"
		::= { statusPhyWifiEntry 9 }

StatusPhyWifiScanEntry ::=
    SEQUENCE {
		statusPhyWifiScanTableIndex INTEGER
		,statusPhyWifiScanSSID OCTET STRING
		,statusPhyWifiScanSignal INTEGER
		,statusPhyWifiScanFreq INTEGER
		,statusPhyWifiScanMode INTEGER
		,statusPhyWifiScanSecurity SecurityModes
		,statusPhyWifiScanBssid PhysAddress
		,statusPhyWifiScanPhyNum INTEGER
		,statusPhyWifiScanChWidth INTEGER
	}

	statusPhyWifiScanTableIndex OBJECT-TYPE
		SYNTAX INTEGER MAX-ACCESS read-only STATUS current
		DESCRIPTION "Radio device index"
		::= { statusPhyWifiScanEntry 1 }

	statusPhyWifiScanSSID OBJECT-TYPE
		SYNTAX OCTET STRING(SIZE(0..32)) MAX-ACCESS read-only STATUS current
		DESCRIPTION "Radio device SSID"
		::= { statusPhyWifiScanEntry 2 }

	statusPhyWifiScanSignal OBJECT-TYPE
		SYNTAX INTEGER MAX-ACCESS read-only STATUS current
		DESCRIPTION "Radio device signal power in dBm"
		::= { statusPhyWifiScanEntry 3}

	statusPhyWifiScanFreq OBJECT-TYPE
		SYNTAX INTEGER MAX-ACCESS read-only STATUS current
		DESCRIPTION "Radio device central frequency (in MHz)"
		::= { statusPhyWifiScanEntry 4 }

	statusPhyWifiScanMode OBJECT-TYPE
		SYNTAX INTEGER {
			unknown(1)
			,infrastructure(2)
			,adhoc(3)
			,mesh(4)
		} MAX-ACCESS read-only STATUS current
		DESCRIPTION "Radio device mode"
		::= { statusPhyWifiScanEntry 5 }

	statusPhyWifiScanSecurity OBJECT-TYPE
		SYNTAX SecurityModes MAX-ACCESS read-only STATUS current
		DESCRIPTION "Radio device mode"
		::= { statusPhyWifiScanEntry 6 }

	statusPhyWifiScanBssid OBJECT-TYPE
		SYNTAX PhysAddress MAX-ACCESS read-only STATUS current
		DESCRIPTION "Radio device bssid"
		::= { statusPhyWifiScanEntry 7 }

	statusPhyWifiScanPhyNum OBJECT-TYPE
		SYNTAX INTEGER MAX-ACCESS read-only STATUS current
		DESCRIPTION "Scan phy index"
		::= { statusPhyWifiScanEntry 8 }

	statusPhyWifiScanChWidth OBJECT-TYPE
		SYNTAX INTEGER MAX-ACCESS read-only STATUS current
		DESCRIPTION "Radio device channel width
					[FW:E2148.AC.1:4.8.0.1]"
		::= { statusPhyWifiScanEntry 9 }

--statusPhyWifiMaxScanSsid OBJECT-TYPE
--	SYNTAX INTEGER MAX-ACCESS read-only STATUS current
--	DESCRIPTION "Max number of scan SSIDs"
--	::= { statusPhyWifiEntry 4 }

--statusPhyWifiRtsThreshold OBJECT-TYPE
--	SYNTAX INTEGER MAX-ACCESS read-only STATUS current
--	DESCRIPTION "RTS threshold"
--	::= { statusPhyWifiEntry 5 }

statusSpanningTreeTable OBJECT-TYPE
	SYNTAX SEQUENCE OF StatusSpanningTreeEntry
	MAX-ACCESS not-accessible STATUS current
	DESCRIPTION "A table that contains information related to STP
		     about every bridge
		    [FW:E2148.AC.1:2.8.0.1]"
	::= { networkStatus 7 }

statusSpanningTreeEntry OBJECT-TYPE
	SYNTAX StatusSpanningTreeEntry
	MAX-ACCESS not-accessible STATUS current
	DESCRIPTION "A list of objects containing information for each Bridge
				 about the Spanning Tree Protocol for that Bridge."
	INDEX { statusSpanningTreeBridgeName }
	::= { statusSpanningTreeTable 1 }

	-- Bridge elements

	StatusSpanningTreeEntry ::=
	    SEQUENCE {
			statusSpanningTreeBridgeName NetifName -- lan
			,statusSpanningTreeNetworkLabel DisplayString
			,statusSpanningTreeBridgeId BridgeId
			,statusSpanningTreeDesignatedRoot BridgeId
			,statusSpanningTreeRootPort NetifName
		}

	statusSpanningTreeBridgeName OBJECT-TYPE
		SYNTAX NetifName
		MAX-ACCESS read-only STATUS current
		DESCRIPTION "Symbolic name of the bridge for which this entry
        			 contains Spanning Tree Protocol management information.
					 Referred to in the general Interfaces table."
		::= { statusSpanningTreeEntry 1 }

	statusSpanningTreeNetworkLabel OBJECT-TYPE
		SYNTAX DisplayString
		MAX-ACCESS read-only STATUS current
		DESCRIPTION "The network label that contains the current bridge."
		::= { statusSpanningTreeEntry 2 }

	statusSpanningTreeBridgeId OBJECT-TYPE
		SYNTAX BridgeId
		MAX-ACCESS read-only STATUS current
		DESCRIPTION "The bridge Id. It is made up using the bridge priority
					 and the base MAC address of the bridge."
		::= { statusSpanningTreeEntry 3 }

	statusSpanningTreeDesignatedRoot OBJECT-TYPE
		SYNTAX BridgeId
		MAX-ACCESS read-only STATUS current
		DESCRIPTION "Root Bridge for the Spanning tree.
					 It is made up using the bridge priority
					 and the base MAC address of the bridge."
		::= { statusSpanningTreeEntry 4 }

	statusSpanningTreeRootPort OBJECT-TYPE
		SYNTAX NetifName
		MAX-ACCESS read-only STATUS current
		DESCRIPTION "The root port name of the current bridge.
					 none is set if there is no root port in the bridge"
		::= { statusSpanningTreeEntry 5 }

statusSpanningTreePortTable OBJECT-TYPE
	SYNTAX SEQUENCE OF StatusSpanningTreePortEntry
	MAX-ACCESS not-accessible STATUS current
	DESCRIPTION "A table that contains port-specific information
		     for the Spanning Tree Protocol.
   		    [FW:E2148.AC.1:2.8.0.1]"
	::= { networkStatus 8 }

statusSpanningTreePortEntry OBJECT-TYPE
	SYNTAX StatusSpanningTreePortEntry
	MAX-ACCESS not-accessible STATUS current
	DESCRIPTION "A list of objects containing information maintained by
				 every port about the Spanning Tree Protocol state
				 for that port."
	INDEX { statusSpanningTreePortBridgeName , statusSpanningTreePortName }
	::= { statusSpanningTreePortTable 1 }

	StatusSpanningTreePortEntry ::=
	    SEQUENCE {
			statusSpanningTreePortBridgeName NetifName
			,statusSpanningTreePortNetworkLabel DisplayString
			,statusSpanningTreePortName NetifName
			,statusSpanningTreePortLabel DisplayString
			,statusSpanningTreePortId PortId
			,statusSpanningTreePortRole INTEGER
			,statusSpanningTreePortState INTEGER
			,statusSpanningTreePortPathCost Integer32
			,statusSpanningTreePortDesignatedRoot BridgeId
			,statusSpanningTreePortDesignatedCost Integer32
			,statusSpanningTreePortDesignatedBridge BridgeId
			,statusSpanningTreePortDesignatedPort PortId
			,statusSpanningTreePortOperEdgePort TruthValue
			,statusSpanningTreePortOperPointToPoint TruthValue
		}

	statusSpanningTreePortBridgeName OBJECT-TYPE
		SYNTAX NetifName
		MAX-ACCESS read-only STATUS current
		DESCRIPTION "Symbolic name of the bridge for which this entry
        			 contains Spanning Tree Protocol management information.
					 Referred to in the general Interfaces table."
		::= { statusSpanningTreePortEntry 1 }

	statusSpanningTreePortNetworkLabel OBJECT-TYPE
		SYNTAX DisplayString
		MAX-ACCESS read-only STATUS current
		DESCRIPTION "The network label that contains the current bridge."
		::= { statusSpanningTreePortEntry 2 }

	statusSpanningTreePortName OBJECT-TYPE
		SYNTAX NetifName
		MAX-ACCESS read-only STATUS current
		DESCRIPTION "The name of the port for which this entry
        			 contains Spanning Tree Protocol management information.
					 Referred to in the general Interfaces table."
		::= { statusSpanningTreePortEntry 3 }

	statusSpanningTreePortLabel OBJECT-TYPE
		SYNTAX DisplayString
		MAX-ACCESS read-only STATUS current
		DESCRIPTION "Port label for the specified port."
		::= { statusSpanningTreePortEntry 4 }

	statusSpanningTreePortId OBJECT-TYPE
		SYNTAX PortId
		MAX-ACCESS read-only STATUS current
		DESCRIPTION "Port identifier for the specified port,
					 it is made up from the port priority
					 and the interface number of the port."
		::= { statusSpanningTreePortEntry 5 }

	statusSpanningTreePortRole OBJECT-TYPE
		SYNTAX INTEGER {
					disabled(0),
					root(1),
					designated(2),
					alternate(3),
					backup(4),
					master(5)
						}
		MAX-ACCESS read-only STATUS current
		DESCRIPTION "The port's current role in the Spanning Tree"
		::= { statusSpanningTreePortEntry 6 }

	statusSpanningTreePortState OBJECT-TYPE
		SYNTAX INTEGER {
					discarding(0),
					learning(1),
					forwarding(2)
						}
		MAX-ACCESS read-only STATUS current
		DESCRIPTION "The port's current state in the Spanning Tree"
		::= { statusSpanningTreePortEntry 7 }

	statusSpanningTreePortPathCost OBJECT-TYPE
		SYNTAX Integer32 (1..200000000)
		MAX-ACCESS read-only STATUS current
		DESCRIPTION "The contribution of this port to the path cost
					 of paths towards the spanning tree root
					 which include this port."
		::= { statusSpanningTreePortEntry 8 }

	statusSpanningTreePortDesignatedRoot OBJECT-TYPE
		SYNTAX BridgeId
		MAX-ACCESS read-only STATUS current
		DESCRIPTION "The unique Bridge Identifier of the Bridge
					 recorded as the Root in the Configuration BPDUs
					 transmitted by the Designated Bridge for the
					 segment to which the port is attached."
		::= { statusSpanningTreePortEntry 9 }

	statusSpanningTreePortDesignatedCost OBJECT-TYPE
		SYNTAX Integer32
		MAX-ACCESS read-only STATUS current
		DESCRIPTION "The path cost of the Designated Port of the segment
					 connected to this port."
		::= { statusSpanningTreePortEntry 10 }

	statusSpanningTreePortDesignatedBridge OBJECT-TYPE
		SYNTAX BridgeId
		MAX-ACCESS read-only STATUS current
		DESCRIPTION "The Bridge Identifier of the Bridge that this
					 port considers to be the Designated Bridge for
					 this port's segment."
		::= { statusSpanningTreePortEntry 11 }

	statusSpanningTreePortDesignatedPort OBJECT-TYPE
		SYNTAX PortId
		MAX-ACCESS read-only STATUS current
		DESCRIPTION "The Port Identifier of the port on the Designated
					 Bridge for this port's segment."
		::= { statusSpanningTreePortEntry 12 }

	statusSpanningTreePortOperEdgePort OBJECT-TYPE
		SYNTAX TruthValue
		MAX-ACCESS read-only STATUS current
		DESCRIPTION "The operational value of the Edge Port parameter.
					 A value of true(1) indicates that this port should be
					 assumed as an edge-port, and a value of false(2) indicates
					 that this port should be assumed as a non-edge-port."
		::= { statusSpanningTreePortEntry 13 }

	statusSpanningTreePortOperPointToPoint OBJECT-TYPE
		SYNTAX TruthValue
		MAX-ACCESS read-only STATUS current
		DESCRIPTION "The operational value of the Point to Point parameter.
					 A value of true(1) indicates that this port is
					 point to point, otherwise set to false(2)"
		::= { statusSpanningTreePortEntry 14 }

statusAssociationTable OBJECT-TYPE
	SYNTAX SEQUENCE OF StatusAssociationEntry
	MAX-ACCESS not-accessible STATUS current
	DESCRIPTION "A table that contains information of associated stations.
   		    [FW:E2148.AC.1:3.12.0.1]"
	::= { networkStatus 9 }

statusAssociationEntry OBJECT-TYPE
	SYNTAX StatusAssociationEntry
	MAX-ACCESS not-accessible STATUS current
	DESCRIPTION "A table that contains information of associated stations."
	INDEX { statusAssociationIndex }
	::= { statusAssociationTable 1 }

	StatusAssociationEntry ::=
	    SEQUENCE {
			statusAssociationIndex INTEGER
			,statusAssociationMacAddr PhysAddress
			,statusAssociationSSID DisplayString
			,statusAssociationBSSID PhysAddress
			,statusAssociationPhy DisplayString
			,statusAssociationSignaldBm INTEGER
			,statusAssociationNoisedBm INTEGER
			,statusAssociationSNR INTEGER
			,statusAssociationWlanIndex INTEGER
			,statusAssociationSecurityMode SecurityModes
		}

	statusAssociationIndex OBJECT-TYPE
		SYNTAX INTEGER MAX-ACCESS read-only STATUS current
		DESCRIPTION "Associated station index"
		::= { statusAssociationEntry 1 }

	statusAssociationMacAddr OBJECT-TYPE
		SYNTAX PhysAddress
		MAX-ACCESS read-only STATUS current
		DESCRIPTION "MAC address of the associated station"
		::= { statusAssociationEntry 2 }

	statusAssociationSSID OBJECT-TYPE
		SYNTAX DisplayString
		MAX-ACCESS read-only STATUS current
		DESCRIPTION "SSID of the associated station"
		::= { statusAssociationEntry 3 }

	statusAssociationBSSID OBJECT-TYPE
		SYNTAX PhysAddress
		MAX-ACCESS read-only STATUS current
		DESCRIPTION "BSSID of the associated station"
		::= { statusAssociationEntry 4 }

	statusAssociationPhy OBJECT-TYPE
		SYNTAX DisplayString
		MAX-ACCESS read-only STATUS current
		DESCRIPTION "radio name of the radio that the station connects"
		::= { statusAssociationEntry 5 }

	statusAssociationSignaldBm OBJECT-TYPE
		SYNTAX INTEGER
		MAX-ACCESS read-only STATUS current
		DESCRIPTION "RSSI level in dBm"
		::= { statusAssociationEntry 6 }

	statusAssociationNoisedBm OBJECT-TYPE
		SYNTAX INTEGER
		MAX-ACCESS read-only STATUS current
		DESCRIPTION "Noise level in dBm"
		::= { statusAssociationEntry 7 }

	statusAssociationSNR OBJECT-TYPE
		SYNTAX INTEGER
		MAX-ACCESS read-only STATUS current
		DESCRIPTION "Signal-to-noise ratio"
		::= { statusAssociationEntry 8 }

	statusAssociationWlanIndex OBJECT-TYPE
		SYNTAX INTEGER
		MAX-ACCESS read-only STATUS current
		DESCRIPTION "Index of the role that the station connects
   		    [FW:E2148.AC.1:3.12.9.1]"
		::= { statusAssociationEntry 9 }

	statusAssociationSecurityMode OBJECT-TYPE
		SYNTAX SecurityModes
		MAX-ACCESS read-only STATUS current
		DESCRIPTION "Security policy
   		    [FW:E2148.CA.1:4.8.0.1-R3]"
		::= { statusAssociationEntry 10 }

statusPhyLanTable OBJECT-TYPE
	SYNTAX SEQUENCE OF StatusPhyLanEntry
	MAX-ACCESS not-accessible STATUS current
	DESCRIPTION "A table that contains information of physical ethernet adapter.
   		    [FW:E2148.AC.1:3.12.0.1]"
	::= { networkStatus 10 }

statusPhyLanEntry OBJECT-TYPE
	SYNTAX StatusPhyLanEntry
	MAX-ACCESS not-accessible STATUS current
	DESCRIPTION "A table that contains information of physical ethernet adapter."
	INDEX { statusPhyLanIndex }
	::= { statusPhyLanTable 1 }

	StatusPhyLanEntry ::=
	    SEQUENCE {
			statusPhyLanIndex INTEGER
			,statusPhyLanName DisplayString
			,statusPhyLanLabel DisplayString
			,statusPhyLanIfIndex INTEGER
		}

	statusPhyLanIndex OBJECT-TYPE
		SYNTAX INTEGER MAX-ACCESS read-only STATUS current
		DESCRIPTION "Physical ethernet index"
		::= { statusPhyLanEntry 1 }

	statusPhyLanName OBJECT-TYPE
		SYNTAX DisplayString MAX-ACCESS read-only STATUS current
		DESCRIPTION "Physical ethernet adapter interface name"
		::= { statusPhyLanEntry 2 }

	statusPhyLanLabel OBJECT-TYPE
		SYNTAX DisplayString MAX-ACCESS read-only STATUS current
		DESCRIPTION "Physical ethernet adapter friendly name"
		::= { statusPhyLanEntry 3 }

	statusPhyLanIfIndex OBJECT-TYPE
		SYNTAX INTEGER MAX-ACCESS read-only STATUS current
		DESCRIPTION "Physical ethernet kernel index"
		::= { statusPhyLanEntry 4 }


statusMeshSurveyTable OBJECT-TYPE
	SYNTAX SEQUENCE OF StatusMeshSurveyEntry
	MAX-ACCESS not-accessible STATUS current
	DESCRIPTION "A table that contains information of mesh survey.
   		    [FW:E2148.AC.1:3.12.9.1]"
	::= { networkStatus 11 }

statusMeshSurveyEntry OBJECT-TYPE
	SYNTAX StatusMeshSurveyEntry
	MAX-ACCESS not-accessible STATUS current
	DESCRIPTION "A table that contains information of mesh survey."
	INDEX { statusMeshSurveyIndex }
	::= { statusMeshSurveyTable 1 }

	StatusMeshSurveyEntry ::=
	    SEQUENCE {
			statusMeshSurveyIndex INTEGER
			,statusMeshSurveyDstMacAddr PhysAddress
			,statusMeshSurveyNextHopMacAddr PhysAddress
			,statusMeshSurveyPhy DisplayString
			,statusMeshSurveyMetric INTEGER
			,statusMeshSurveyDiscoveryTimeout INTEGER
			,statusMeshSurveyDiscoveryRetries INTEGER
			,statusMeshSurveyStateActive TruthValue
			,statusMeshSurveyStateResolving TruthValue
			,statusMeshSurveyStateDSNValid TruthValue
			,statusMeshSurveyStateFixed TruthValue
			,statusMeshSurveyStateResolved TruthValue
			,statusMeshSurveyMeshId DisplayString
			,statusMeshSurveyWlanIndex INTEGER
		}

	statusMeshSurveyIndex OBJECT-TYPE
		SYNTAX INTEGER MAX-ACCESS read-only STATUS current
		DESCRIPTION "Mesh survey index"
		::= { statusMeshSurveyEntry 1 }

	statusMeshSurveyDstMacAddr OBJECT-TYPE
		SYNTAX PhysAddress
		MAX-ACCESS read-only STATUS current
		DESCRIPTION "Destination MAC address of the mesh path"
		::= { statusMeshSurveyEntry 2 }

	statusMeshSurveyNextHopMacAddr OBJECT-TYPE
		SYNTAX PhysAddress
		MAX-ACCESS read-only STATUS current
		DESCRIPTION "MAC address of the next mesh point to reach destination MAC address"
		::= { statusMeshSurveyEntry 3 }

	statusMeshSurveyPhy OBJECT-TYPE
		SYNTAX DisplayString
		MAX-ACCESS read-only STATUS current
		DESCRIPTION "Radio name of the mesh path"
		::= { statusMeshSurveyEntry 4 }

	statusMeshSurveyMetric OBJECT-TYPE
		SYNTAX INTEGER
		MAX-ACCESS read-only STATUS current
		DESCRIPTION "Total cost of the mesh path"
		::= { statusMeshSurveyEntry 5 }

	statusMeshSurveyDiscoveryTimeout OBJECT-TYPE
		SYNTAX INTEGER
		MAX-ACCESS read-only STATUS current
		DESCRIPTION "Current discovery timeout for the mesh path"
		::= { statusMeshSurveyEntry 6 }

	statusMeshSurveyDiscoveryRetries OBJECT-TYPE
		SYNTAX INTEGER
		MAX-ACCESS read-only STATUS current
		DESCRIPTION "The number of discovery retries"
		::= { statusMeshSurveyEntry 7 }

	statusMeshSurveyStateActive OBJECT-TYPE
		SYNTAX TruthValue
		MAX-ACCESS read-only STATUS current
		DESCRIPTION "State Active: a value of true(1) indicates that the mesh path can be used for forwording"
		::= { statusMeshSurveyEntry 8 }

	statusMeshSurveyStateResolving OBJECT-TYPE
		SYNTAX TruthValue
		MAX-ACCESS read-only STATUS current
		DESCRIPTION "State Resolving: a value of true(1) indicates that the discovery process for the mesh
					path is running"
		::= { statusMeshSurveyEntry 9 }

	statusMeshSurveyStateDSNValid OBJECT-TYPE
		SYNTAX TruthValue
		MAX-ACCESS read-only STATUS current
		DESCRIPTION "State DSN Valid: a value of true(1) indicates that the mesh path contains a valid
					destination sequence number"
		::= { statusMeshSurveyEntry 10 }

	statusMeshSurveyStateFixed OBJECT-TYPE
		SYNTAX TruthValue
		MAX-ACCESS read-only STATUS current
		DESCRIPTION "State Fixed: a value of true(1) indicates that the status of the mesh path is fixed"
		::= { statusMeshSurveyEntry 11 }

	statusMeshSurveyStateResolved OBJECT-TYPE
		SYNTAX TruthValue
		MAX-ACCESS read-only STATUS current
		DESCRIPTION "State Resolved: a value of true(1) indicates that the discovery process ends successfully"
		::= { statusMeshSurveyEntry 12 }

	statusMeshSurveyMeshId OBJECT-TYPE
		SYNTAX DisplayString
		MAX-ACCESS read-only STATUS current
		DESCRIPTION "Mesh ID string of the mesh path"
		::= { statusMeshSurveyEntry 13 }

	statusMeshSurveyWlanIndex OBJECT-TYPE
		SYNTAX INTEGER
		MAX-ACCESS read-only STATUS current
		DESCRIPTION "Wlan index of the mesh path"
		::= { statusMeshSurveyEntry 14 }

statusPhyCellTable OBJECT-TYPE
	SYNTAX SEQUENCE OF StatusPhyCellEntry
	MAX-ACCESS not-accessible
	STATUS current
	DESCRIPTION "This table contains information about cellular adapters.
		[FW:E2148.AC.1:3.16.1.1]"
	::= { networkStatus 12 }

statusPhyCellEntry OBJECT-TYPE
	SYNTAX StatusPhyCellEntry
	MAX-ACCESS not-accessible
	STATUS current
	DESCRIPTION
		"Details about a cellular adapter
		[FW:E2148.AC.1:3.16.1.1]"
	INDEX { statusPhyCellIndex }
	::= { statusPhyCellTable 1 }

-- Elements in the cellular cards status table

-- Registration status according to 3GPP TS 27.007
CellAttachMode ::= INTEGER {
	reg-hung(0), reg-home(1), reg-searching(2), reg-denied(3),
	reg-noCell(4), reg-roaming(5), reg-homeSMS(6), reg-roamingSMS(7),
	reg-emgOnly(8), reg-homeNoCSFB(9), reg-roamingNoCSFB(10) }

-- Access Technology according to 3GPP TS 27.007
CellAccessTech ::= INTEGER {
	at-gsm(0), at-gsmCompact(1), at-UTRAN(2), at-EGPRS(3), at-HSDPA(4),
	at-HSUPA(5), at-HSPA(6), at-EUTRAN(7), at-GSM-IoT(8), at-EUTRAN-NB-S1(9) }

StatusPhyCellEntry ::=
    SEQUENCE {
		statusPhyCellIndex INTEGER
		,statusPhyCellLabel DisplayString
		,statusPhyCellFriendlyName OCTET STRING
		,statusPhyCellEnable DisableEnable
		,statusPhyCellIMEI DisplayString
		,statusPhyCellModel DisplayString
		,statusPhyCellName NetifName
		,statusPhyCellSimSelected INTEGER
		,statusPhyCellSimState DisplayString
		,statusPhyCellSimIMSI DisplayString
		,statusPhyCellAttachMode CellAttachMode
		,statusPhyCellOperator DisplayString
		,statusPhyCellMcc INTEGER
		,statusPhyCellMnc INTEGER
		,statusPhyCellBaseLAC INTEGER
		,statusPhyCellBaseCID INTEGER
		,statusPhyCellRegistrationClass DisplayString -- gsm or cdma
		,statusPhyCellAccessTech CellAccessTech
		,statusPhyCellBandName DisplayString
		,statusPhyCellARFCN INTEGER
		,statusPhyCellRSSI INTEGER
		,statusPhyCellBER INTEGER
	}

	statusPhyCellIndex OBJECT-TYPE
		SYNTAX INTEGER MAX-ACCESS read-only STATUS current
		DESCRIPTION "Cellular adapter index
		[FW:E2148.AC.1:3.16.1.1]"
		::= { statusPhyCellEntry 1 }

	statusPhyCellLabel OBJECT-TYPE
		SYNTAX DisplayString MAX-ACCESS read-only STATUS current
		DESCRIPTION "The label physically identifying the antennas set on the device
		[FW:E2148.AC.1:3.16.1.1]"
		::= { statusPhyCellEntry 2 }

	statusPhyCellFriendlyName OBJECT-TYPE
		SYNTAX OCTET STRING MAX-ACCESS read-only STATUS current
		DESCRIPTION "Friendly name for this cellular adapter
		[FW:E2148.AC.1:3.16.1.1]"
		::= { statusPhyCellEntry 3 }

	statusPhyCellEnable OBJECT-TYPE
		SYNTAX DisableEnable MAX-ACCESS read-only STATUS current
		DESCRIPTION "Administrative state
		[FW:E2148.AC.1:3.16.1.1]"
		::= { statusPhyCellEntry 4 }

	statusPhyCellIMEI OBJECT-TYPE
		SYNTAX DisplayString MAX-ACCESS read-only STATUS current
		DESCRIPTION "Adapter IMEI
		[FW:E2148.AC.1:3.16.1.1]"
		::= { statusPhyCellEntry 5 }

	statusPhyCellModel OBJECT-TYPE
		SYNTAX DisplayString MAX-ACCESS read-only STATUS current
		DESCRIPTION "Manufacturer adapter ID
		[FW:E2148.AC.1:3.16.1.1]"
		::= { statusPhyCellEntry 6 }

	statusPhyCellName OBJECT-TYPE
		SYNTAX NetifName MAX-ACCESS read-only STATUS current
		DESCRIPTION "Symbolic identifier for the adapter
		[FW:E2148.AC.1:3.16.1.1]"
		::= { statusPhyCellEntry 7 }

	statusPhyCellSimSelected OBJECT-TYPE
		SYNTAX INTEGER MAX-ACCESS read-only STATUS current
		DESCRIPTION "SIM card currently in use (1 or 2, 0=unknown)
		[FW:E2148.AC.1:3.16.1.1]"
		::= { statusPhyCellEntry 8 }

	statusPhyCellSimState OBJECT-TYPE
		SYNTAX DisplayString MAX-ACCESS read-only STATUS current
		DESCRIPTION "SIM state, see 3GPP TS27.007 +CPIN
		[FW:E2148.AC.1:3.16.1.1]"
		::= { statusPhyCellEntry 9 }

	statusPhyCellSimIMSI OBJECT-TYPE
		SYNTAX DisplayString MAX-ACCESS read-only STATUS current
		DESCRIPTION "Subscriber identity (IMSI)
		[FW:E2148.AC.1:3.16.1.1]"
		::= { statusPhyCellEntry 10 }

	statusPhyCellAttachMode OBJECT-TYPE
		SYNTAX CellAttachMode MAX-ACCESS read-only STATUS current
		DESCRIPTION "Network registration state, see 3GPP TS27.007 +CREG
		[FW:E2148.AC.1:3.16.1.1]"
		::= { statusPhyCellEntry 11 }

	statusPhyCellOperator OBJECT-TYPE
		SYNTAX DisplayString MAX-ACCESS read-only STATUS current
		DESCRIPTION "Telecom operator name
		[FW:E2148.AC.1:3.16.1.1]"
		::= { statusPhyCellEntry 12 }

	statusPhyCellMcc OBJECT-TYPE
		SYNTAX INTEGER MAX-ACCESS read-only STATUS current
		DESCRIPTION "Mobile Country Code
		[FW:E2148.AC.1:3.16.1.1]"
		::= { statusPhyCellEntry 13 }

	statusPhyCellMnc OBJECT-TYPE
		SYNTAX INTEGER MAX-ACCESS read-only STATUS current
		DESCRIPTION "Mobile Network (Operator) Code
		[FW:E2148.AC.1:3.16.1.1]"
		::= { statusPhyCellEntry 14 }

	statusPhyCellBaseLAC OBJECT-TYPE
		SYNTAX INTEGER MAX-ACCESS read-only STATUS current
		DESCRIPTION "Location Area Code
		[FW:E2148.AC.1:3.16.1.1]"
		::= { statusPhyCellEntry 15 }

	statusPhyCellBaseCID OBJECT-TYPE
		SYNTAX INTEGER MAX-ACCESS read-only STATUS current
		DESCRIPTION "Cell ID
		[FW:E2148.AC.1:3.16.1.1]"
		::= { statusPhyCellEntry 16 }

	statusPhyCellRegistrationClass OBJECT-TYPE
		SYNTAX DisplayString MAX-ACCESS read-only STATUS current
		DESCRIPTION "Registration class (gsm, cdma)
		[FW:E2148.AC.1:3.16.1.1]"
		::= { statusPhyCellEntry 17 }

	statusPhyCellAccessTech OBJECT-TYPE
		SYNTAX CellAccessTech MAX-ACCESS read-only STATUS current
		DESCRIPTION "Access Technology, see 3GPP TS27.007 +CREG
		[FW:E2148.AC.1:3.16.1.1]"
		::= { statusPhyCellEntry 18 }

	statusPhyCellBandName OBJECT-TYPE
		SYNTAX DisplayString MAX-ACCESS read-only STATUS current
		DESCRIPTION "Radio band
		[FW:E2148.AC.1:3.16.1.1]"
		::= { statusPhyCellEntry 19 }

	statusPhyCellARFCN OBJECT-TYPE
		SYNTAX INTEGER MAX-ACCESS read-only STATUS current
		DESCRIPTION "Channel (ARFCN)
		[FW:E2148.AC.1:3.16.1.1]"
		::= { statusPhyCellEntry 20 }

	statusPhyCellRSSI OBJECT-TYPE
		SYNTAX INTEGER MAX-ACCESS read-only STATUS current
		DESCRIPTION "Signal quality (RSSI)
		[FW:E2148.AC.1:3.16.1.1]"
		::= { statusPhyCellEntry 21 }

	statusPhyCellBER OBJECT-TYPE
		SYNTAX INTEGER MAX-ACCESS read-only STATUS current
		DESCRIPTION "Bit Error Rate Estimator (see 3GPP TS45.008)
		[FW:E2148.AC.1:3.16.1.1]"
		::= { statusPhyCellEntry 22 }

statusRoaming OBJECT IDENTIFIER ::= { networkStatus 13 }

statusRoamingLeaveLvlMax OBJECT-TYPE
	SYNTAX INTEGER
	MAX-ACCESS read-only STATUS current
	DESCRIPTION "When current AP's signal level is above this value, roaming will occur when possible.
	[FW:E2148.AC.1:4.10.0.1]"
	::= { statusRoaming 1 }

statusRoamingLeaveLvlMin OBJECT-TYPE
	SYNTAX INTEGER
	MAX-ACCESS read-only STATUS current
	DESCRIPTION "When current AP's signal level is below this value, roaming will occur when possible.
	[FW:E2148.AC.1:4.10.0.1]"
	::= { statusRoaming 2 }

statusRoamingRoamLvlMax OBJECT-TYPE
	SYNTAX INTEGER
	MAX-ACCESS read-only STATUS current
	DESCRIPTION "When the signal level of an AP in scan result is above this value, it will not be considered as a candidate.
	[FW:E2148.AC.1:4.10.0.1]"
	::= { statusRoaming 3 }

statusRoamingRoamLvlMin OBJECT-TYPE
	SYNTAX INTEGER
	MAX-ACCESS read-only STATUS current
	DESCRIPTION "When the signal level of an AP in scan result is below this value, it will not be considered as a candidate.
	[FW:E2148.AC.1:4.10.0.1]"
	::= { statusRoaming 4 }

statusRoamingThresHyst OBJECT-TYPE
	SYNTAX INTEGER
	MAX-ACCESS read-only STATUS current
	DESCRIPTION "The hysteresis applied in all thresholds
	[FW:E2148.AC.1:4.10.0.1]"
	::= { statusRoaming 5 }

statusRoamingLeaveBoost OBJECT-TYPE
	SYNTAX INTEGER
	MAX-ACCESS read-only STATUS current
	DESCRIPTION "Roaming occurs only if the candidate signal level is above the current AP's plus this value.
	[FW:E2148.AC.1:4.10.0.1]"
	::= { statusRoaming 6 }

statusRoamingActiveIf OBJECT IDENTIFIER ::= { statusRoaming 7 }

statusRoamingActiveIfName OBJECT-TYPE
	SYNTAX OCTET STRING
	MAX-ACCESS read-only STATUS current
	DESCRIPTION "Name of active roaming interface
	[FW:E2148.AC.1:4.10.0.1]"
	::= { statusRoamingActiveIf 1 }

statusRoamingActiveIfBssid OBJECT-TYPE
	SYNTAX PhysAddress
	MAX-ACCESS read-only STATUS current
	DESCRIPTION "BSSID of active roaming interface
	[FW:E2148.AC.1:4.10.0.1]"
	::= { statusRoamingActiveIf 2 }

statusRoamingActiveIfBeaconSignalAvg OBJECT-TYPE
	SYNTAX INTEGER MAX-ACCESS read-only STATUS current
	DESCRIPTION "Signal level average in dBm of the last few beacons received
	[FW:E2148.AC.1:4.10.0.1]"
	::= { statusRoamingActiveIf 3 }

statusRoamingActiveIfNoise OBJECT-TYPE
	SYNTAX INTEGER
	MAX-ACCESS read-only STATUS current
	DESCRIPTION "Noise level of active roaming interface
	[FW:E2148.AC.1:4.10.0.1]"
	::= { statusRoamingActiveIf 4 }

statusRoamingActiveIfSwitching OBJECT-TYPE
	SYNTAX INTEGER { false(1), true(2) }
	MAX-ACCESS read-only STATUS current
	DESCRIPTION "If roaming interface is switching
	[FW:E2148.AC.1:4.10.0.1]"
	::= { statusRoamingActiveIf 5 }

statusRoamingActiveIfChannel OBJECT-TYPE
	SYNTAX INTEGER MAX-ACCESS read-only STATUS current
	DESCRIPTION "Wlan channel (frequency span index):
	-1 channel indicates that the product is searching for a channel
	[FW:E2148.AC.1:4.12.0.1]"
	::= { statusRoamingActiveIf 6 }

statusRoamingActiveIfState OBJECT-TYPE
	SYNTAX INTEGER {
			not-connected(0)
			,connected(9)
			}
	MAX-ACCESS read-only STATUS current
	DESCRIPTION "Connection state
	[FW:E2148.AC.1:4.12.0.1]"
	::= { statusRoamingActiveIf 7 }

statusRoamingPassiveIf OBJECT IDENTIFIER ::= { statusRoaming 8 }

statusRoamingPassiveIfName OBJECT-TYPE
	SYNTAX OCTET STRING
	MAX-ACCESS read-only STATUS current
	DESCRIPTION "Name of passive roaming interface
	[FW:E2148.AC.1:4.10.0.1]"
	::= { statusRoamingPassiveIf 1 }

statusRoamingPassiveIfBssid OBJECT-TYPE
	SYNTAX PhysAddress
	MAX-ACCESS read-only STATUS current
	DESCRIPTION "BSSID of passive roaming interface
	[FW:E2148.AC.1:4.10.0.1]"
	::= { statusRoamingPassiveIf 2 }

statusRoamingPassiveIfBeaconSignalAvg OBJECT-TYPE
	SYNTAX INTEGER MAX-ACCESS read-only STATUS current
	DESCRIPTION "Signal level average in dBm of the last few beacons received
	[FW:E2148.AC.1:4.10.0.1]"
	::= { statusRoamingPassiveIf 3 }

statusRoamingPassiveIfNoise OBJECT-TYPE
	SYNTAX INTEGER
	MAX-ACCESS read-only STATUS current
	DESCRIPTION "Noise level of passive roaming interface
	[FW:E2148.AC.1:4.10.0.1]"
	::= { statusRoamingPassiveIf 4 }

statusRoamingPassiveIfSwitching OBJECT-TYPE
	SYNTAX INTEGER { false(1), true(2) }
	MAX-ACCESS read-only STATUS current
	DESCRIPTION "If roaming interface is switching
	[FW:E2148.AC.1:4.10.0.1]"
	::= { statusRoamingPassiveIf 5 }

statusRoamingPassiveIfChannel OBJECT-TYPE
	SYNTAX INTEGER MAX-ACCESS read-only STATUS current
	DESCRIPTION "Wlan channel (frequency span index):
	-1 channel indicates that the product is searching for a channel
	[FW:E2148.AC.1:4.12.0.1]"
	::= { statusRoamingPassiveIf 6 }

statusRoamingPassiveIfState OBJECT-TYPE
	SYNTAX INTEGER {
			not-connected(0)
			,connected(9)
			}
	MAX-ACCESS read-only STATUS current
	DESCRIPTION "Connection state
	[FW:E2148.AC.1:4.12.0.1]"
	::= { statusRoamingPassiveIf 7 }

statusRoamingUrgent OBJECT-TYPE
	SYNTAX DisableEnable MAX-ACCESS read-only STATUS current DESCRIPTION
	"PLH algorithm 'Urgent' indication.
	Disable: normal condition.
	Enable: the current AP is below the urgent level, and there is
	no candidate AP complying with the candidate selection rules.
	[FW:E2148.AC.1:4.12.0.1]"
    ::= { statusRoaming 9 }

-- =========================================
-- networkConfiguration (config files state)
--
tcpip OBJECT IDENTIFIER ::= { networkConfiguration 1 }
netphy OBJECT IDENTIFIER ::= { networkConfiguration 2 }
netif OBJECT IDENTIFIER ::= { networkConfiguration 3 }
roaming OBJECT IDENTIFIER ::= { networkConfiguration 4 }
netdetails OBJECT IDENTIFIER ::= { netif 1 }

-- Tables - radio devices configuration {

configPhyWifiTable OBJECT-TYPE
	SYNTAX SEQUENCE OF ConfigPhyWifiEntry
	MAX-ACCESS not-accessible
	STATUS current
	DESCRIPTION
		"List of Wi-Fi radio devices
		[FW:E2148.AC.1:2.8.0.1]"
	::= { netphy 1 }

configPhyWifiEntry OBJECT-TYPE
	SYNTAX ConfigPhyWifiEntry
	MAX-ACCESS not-accessible
	STATUS current
	DESCRIPTION
		"Details about a Wi-Fi service set
		[FW:E2148.AC.1:2.8.0.1]"
	INDEX { configPhyWifiName } -- radio0, radio1
	::= { configPhyWifiTable 1 }

	-- Elements in the radio cards config table

	ConfigPhyWifiEntry ::=
	    SEQUENCE {
			configPhyWifiName NetifName
			,configPhyWifiLabel DisplayString
			,configPhyWifiMAC PhysAddress
			,configPhyWifiEnable DisableEnable
			,configPhyWifiMode WifiFlavor
			,configPhyWifiCountry OCTET STRING
			,configPhyWifiChannel INTEGER
			,configPhyWifiHTMode INTEGER
			,configPhyWifiTxPowerDBM INTEGER
			,configPhyWifiDistance INTEGER
			,configPhyWifiClusterMode OCTET STRING
			,configPhyWifiClusterList OCTET STRING
			,configPhyWifiClusterArgs OCTET STRING
			,configPhyWifiAntennaPorts INTEGER
			,configPhyWifiABGBasicRates OCTET STRING
			,configPhyWifiABGSupportedRates OCTET STRING
			,configPhyWifiChannelList OCTET STRING
			,configPhyWifiWids INTEGER
		}
	-- { configPhyWifiEntry 1 } never used

	configPhyWifiName OBJECT-TYPE
		SYNTAX NetifName MAX-ACCESS read-only STATUS current
		DESCRIPTION "Symbolic identifier for the radio device"
		::= { configPhyWifiEntry 2 }

	configPhyWifiLabel OBJECT-TYPE
		SYNTAX DisplayString MAX-ACCESS read-only STATUS current
		DESCRIPTION "The label physically identifying the antennas set on the device
		[phywifi]"
		::= { configPhyWifiEntry 3 }

	configPhyWifiMAC OBJECT-TYPE
		SYNTAX PhysAddress MAX-ACCESS read-only STATUS current
		DESCRIPTION "MAC address of the radio device"
		::= { configPhyWifiEntry 4 }

	configPhyWifiEnable OBJECT-TYPE
		SYNTAX DisableEnable
		MAX-ACCESS read-write STATUS current
		DESCRIPTION "Configured state"
		::= { configPhyWifiEntry 5 }

	configPhyWifiMode OBJECT-TYPE
		SYNTAX WifiFlavor
		MAX-ACCESS read-write STATUS current
		DESCRIPTION "Configured 802.11 flavor.
					-1 indicates invalid value."
		::= { configPhyWifiEntry 6 }

	configPhyWifiCountry OBJECT-TYPE
		SYNTAX OCTET STRING(SIZE(0..5))
		MAX-ACCESS read-write STATUS current
		DESCRIPTION "Country for regulatory checks on channel/power"
		::= { configPhyWifiEntry 7 }

	configPhyWifiChannel OBJECT-TYPE
		SYNTAX INTEGER
		MAX-ACCESS read-write STATUS current
		DESCRIPTION "Configured radio channel (frequency span index)
		A value of 0 indicates that your radio device is configured on multiple channels or automatic channel select.
		See configPhyWifiChannelList for more channel details.
		Ignored in client roaming mode, see configIfStaScanChannels instead."
		::= { configPhyWifiEntry 8 }

	configPhyWifiHTMode OBJECT-TYPE
		SYNTAX INTEGER {ht20(1),ht40-below(2),ht40-above(3),ht40-auto(4),vht20(5),vht40(6),vht80(7)}
		MAX-ACCESS read-write STATUS current
		DESCRIPTION "802.11n channel width. Double (40) width is
			subject to automatic availability checking before use."
		::= { configPhyWifiEntry 9 }

	configPhyWifiTxPowerDBM OBJECT-TYPE
		SYNTAX INTEGER
		MAX-ACCESS read-write STATUS current
		DESCRIPTION "Configured radio transmit power limit in dBm.
			To transmit with the maximum allowed power, use
			value '-1'."
		::= { configPhyWifiEntry 10 }

	configPhyWifiDistance OBJECT-TYPE
		SYNTAX INTEGER
		MAX-ACCESS read-write STATUS current
		DESCRIPTION "Configured maximum distance between AP and stations (meters)"
		::= { configPhyWifiEntry 11 }

	configPhyWifiClusterMode OBJECT-TYPE
		SYNTAX OCTET STRING(SIZE(0..16))
		MAX-ACCESS read-write STATUS current
		DESCRIPTION "Cluster mode, empty for none, 'dualscan' for data/scan separation"
		::= { configPhyWifiEntry 12 }

	configPhyWifiClusterList OBJECT-TYPE
		SYNTAX OCTET STRING(SIZE(0..64))
		MAX-ACCESS read-write STATUS current
		DESCRIPTION "List of device names in the cluster, e.g. 'radio0 radio1'"
		::= { configPhyWifiEntry 13 }

	configPhyWifiClusterArgs OBJECT-TYPE
		SYNTAX OCTET STRING(SIZE(0..64))
		MAX-ACCESS read-write STATUS current
		DESCRIPTION "Cluster params for this device. For 'dualscan' mode,
				one device must be set to 'scan',
				the others in the cluster must be set to 'data'."
		::= { configPhyWifiEntry 14 }

	configPhyWifiAntennaPorts OBJECT-TYPE
		SYNTAX INTEGER {
			port1(1)
			,ports12(3)
			,ports123(7)
		}
		MAX-ACCESS read-write STATUS current
		DESCRIPTION "Antenna port configuration."
		::= { configPhyWifiEntry 15 }

	configPhyWifiABGBasicRates OBJECT-TYPE
		SYNTAX OCTET STRING(SIZE(4..66))
		MAX-ACCESS read-write STATUS current
		DESCRIPTION "Space separated list of basic rates (in kbps).
					A value of 0 indicates that your radio device is configured on automatic basic rate."
		::= { configPhyWifiEntry 16 }

	configPhyWifiABGSupportedRates OBJECT-TYPE
		SYNTAX OCTET STRING(SIZE(4..66))
		MAX-ACCESS read-write STATUS current
		DESCRIPTION "Space separated list of supported rates (in kbps).
					A value of 0 indicates that your radio device is configured on automatic supported rate."
		::= { configPhyWifiEntry 17 }

	configPhyWifiChannelList OBJECT-TYPE
		SYNTAX OCTET STRING
		MAX-ACCESS read-write STATUS current
		DESCRIPTION "Configured radio channel list:
		Display/enter one or several channels, separated by spaces.
		'auto' or '0' indicates automatic channel select.
		Ignored in client roaming mode, see configIfStaScanChannels instead."
		::= { configPhyWifiEntry 18 }

	configPhyWifiWids OBJECT-TYPE
		SYNTAX INTEGER MAX-ACCESS read-write STATUS current
		DESCRIPTION "WIDS functions selection.
		0: radio is not reserved for WIDS (default).
		1: radio is reserved for rogue AP monitoring.
		[FW:E2148.AC.1:4.16.0.1]"
		::= { configPhyWifiEntry 19 }

configPhyCellTable OBJECT-TYPE
	SYNTAX SEQUENCE OF ConfigPhyCellEntry
	MAX-ACCESS not-accessible
	STATUS current
	DESCRIPTION
		"List of Cellular radio devices
		[FW:E2148.AC.1:4.12.0.1]"
	::= { netphy 2 }

configPhyCellEntry OBJECT-TYPE
	SYNTAX ConfigPhyCellEntry
	MAX-ACCESS not-accessible
	STATUS current
	DESCRIPTION
		"Details about a cellular radio device"
	INDEX { configPhyCellName } -- wwan0, wwan1: uciname
	::= { configPhyCellTable 1 }

	-- Elements in the radio cards config table

	ConfigPhyCellEntry ::= SEQUENCE {
		configPhyCellName NetifName
		,configPhyCellLabel DisplayString
		,configPhyCellDisableAtBoot DisableEnable
		,configPhyCellLogAT DisableEnable
		,configPhyCellSIM INTEGER
		,configPhyCellSetPIN DisplayString
		,configPhyCellSetPUK DisplayString
		,configPhyCellSetPINStatus AsyncSetStatus
		,configPhyCellSim1Pin DisplayString
		,configPhyCellSim1Apn DisplayString
		,configPhyCellSim1Authentication CellSecurityProtocol
		,configPhyCellSim1Identity DisplayString
		,configPhyCellSim1Password DisplayString
		,configPhyCellSim2Pin DisplayString
		,configPhyCellSim2Apn DisplayString
		,configPhyCellSim2Authentication CellSecurityProtocol
		,configPhyCellSim2Identity DisplayString
		,configPhyCellSim2Password DisplayString
	}

	configPhyCellName OBJECT-TYPE
		SYNTAX NetifName MAX-ACCESS read-only STATUS current
		DESCRIPTION "Symbolic identifier for the radio device"
		::= { configPhyCellEntry 1 }

	configPhyCellLabel OBJECT-TYPE
		SYNTAX DisplayString MAX-ACCESS read-only STATUS current
		DESCRIPTION "The label physically identifying the
				plugs/indicators on the device box
				[PF:wwan:0]"
		::= { configPhyCellEntry 2 }

	configPhyCellDisableAtBoot OBJECT-TYPE
		SYNTAX DisableEnable MAX-ACCESS read-write STATUS current
		DESCRIPTION "Set the card to be forcibly disabled at boot time.
			If set to Enable, the associated network will be
			initially disabled after reboots.
			If set to Disable, the associated network will obey
			its existing configuration."
		::= { configPhyCellEntry 3 }

	configPhyCellLogAT OBJECT-TYPE
		SYNTAX DisableEnable MAX-ACCESS read-write STATUS current
		DESCRIPTION "Enable logging of internal AT commands/responses"
		::= { configPhyCellEntry 4 }

	configPhyCellSIM OBJECT-TYPE
		SYNTAX INTEGER { sim1(1), sim2(2) }
		MAX-ACCESS read-write STATUS current
		DESCRIPTION "Default SIM/UICC activated at startup
			(for Dual SIM Single Standby radios)"
		::= { configPhyCellEntry 5 }

	configPhyCellSetPIN OBJECT-TYPE
		SYNTAX DisplayString MAX-ACCESS read-write STATUS current
		DESCRIPTION "Not implemented. New PIN code value
			to set in the *currently selected* SIM card.
			Reading this OID returns nothing.
			WARNING 1: the corresponding configPhyCellSim(1/2)Pin
			OID will retain its previous value; you must set it
			separately to its new value in order to use that SIM
			WARNING 2: this field is volatile and used either
			immediately or just after setting the PUK, as required"
		::= { configPhyCellEntry 6 }

	configPhyCellSetPUK OBJECT-TYPE
		SYNTAX DisplayString MAX-ACCESS read-write STATUS current
		DESCRIPTION "Not implemented. PUK code required to reset
			the PIN code of the *currently selected* SIM card to
			the value of configPhyCellSetPIN.
			Use this only if the SIM is locked after an excessive
			number of PIN code errors
			Reading this OID returns nothing.
			WARNING: this field is volatile and used immediately,
			then cleared out"
		::= { configPhyCellEntry 7 }

	configPhyCellSetPINStatus OBJECT-TYPE
		SYNTAX AsyncSetStatus MAX-ACCESS read-only STATUS current
		DESCRIPTION "Not implemented.
			Status of a write operation to configPhyCellSetPIN /
			configPhyCellSetPUK.
			set-init: no operation was requested yet
			set-more: more data (PUK code) needed
			set-wait: operation in progress
			set-ok: operation finished and succeeded
			set-fail: operation finished and failed"
		::= { configPhyCellEntry 8 }

	configPhyCellSim1Pin OBJECT-TYPE
		SYNTAX DisplayString MAX-ACCESS read-write STATUS current
		DESCRIPTION "PIN code required to enable the SIM card"
		::= { configPhyCellEntry 9 }

	configPhyCellSim1Apn OBJECT-TYPE
		SYNTAX DisplayString MAX-ACCESS read-write STATUS current
		DESCRIPTION "APN - Name of the cellular sub-service
			for IP. If left empty, the default subscriber's
			APN will be used"
		::= { configPhyCellEntry 10 }

	configPhyCellSim1Authentication OBJECT-TYPE
		SYNTAX CellSecurityProtocol MAX-ACCESS read-write STATUS current
		DESCRIPTION "Authentication type towards the Telecom network"
		::= { configPhyCellEntry 11 }

	configPhyCellSim1Identity OBJECT-TYPE
		SYNTAX DisplayString MAX-ACCESS read-write STATUS current
		DESCRIPTION "User name for PAP/CHAP authentication"
		::= { configPhyCellEntry 12 }

	configPhyCellSim1Password OBJECT-TYPE
		SYNTAX DisplayString MAX-ACCESS read-write STATUS current
		DESCRIPTION "User password for PAP/CHAP authentication"
		::= { configPhyCellEntry 13 }

	configPhyCellSim2Pin OBJECT-TYPE
		SYNTAX DisplayString MAX-ACCESS read-write STATUS current
		DESCRIPTION "PIN code required to enable the SIM card"
		::= { configPhyCellEntry 14 }

	configPhyCellSim2Apn OBJECT-TYPE
		SYNTAX DisplayString MAX-ACCESS read-write STATUS current
		DESCRIPTION "APN - Name of the cellular sub-service
			for IP. If left empty, the default subscriber's
			APN will be used"
		::= { configPhyCellEntry 15 }

	configPhyCellSim2Authentication OBJECT-TYPE
		SYNTAX CellSecurityProtocol MAX-ACCESS read-write STATUS current
		DESCRIPTION "Authentication type towards the Telecom network"
		::= { configPhyCellEntry 16 }

	configPhyCellSim2Identity OBJECT-TYPE
		SYNTAX DisplayString MAX-ACCESS read-write STATUS current
		DESCRIPTION "User name for PAP/CHAP authentication"
		::= { configPhyCellEntry 17 }

	configPhyCellSim2Password OBJECT-TYPE
		SYNTAX DisplayString MAX-ACCESS read-write STATUS current
		DESCRIPTION "User password for PAP/CHAP authentication"
		::= { configPhyCellEntry 18 }

-- Tables - radio devices configuration }

-- Table - Radius servers {

configRadiusTable OBJECT-TYPE
	SYNTAX SEQUENCE OF ConfigRadiusEntry
	MAX-ACCESS not-accessible
	STATUS current
	DESCRIPTION
		"List of radius servers currently defined
		[FW:E2148.AC.1:2.8.0.1]"
	::= { netdetails 1 }

configRadiusEntry OBJECT-TYPE
	SYNTAX ConfigRadiusEntry
	MAX-ACCESS not-accessible
	STATUS current
	DESCRIPTION
		"Details about a radius server
		[FW:E2148.AC.1:2.8.0.1]"
	INDEX { configRadiusIndex } -- en nombre limité, UCI 'radius'
	::= { configRadiusTable 1 }

	-- Elements in the IP subnet status table

	ConfigRadiusEntry ::=
	    SEQUENCE {
			configRadiusIndex INTEGER,
			configRadiusRowStatus RowStatus,
			configRadiusIpAddress OCTET STRING,
			configRadiusPort INTEGER,
			configRadiusSecret OCTET STRING
		}

	configRadiusIndex OBJECT-TYPE
		SYNTAX INTEGER MAX-ACCESS read-only STATUS current
		DESCRIPTION "Radius index, maximum 4 items support"
		::= { configRadiusEntry 1 }

	configRadiusRowStatus OBJECT-TYPE
		SYNTAX RowStatus MAX-ACCESS read-create STATUS current
		DESCRIPTION "row addition/deletion support"
		::= { configRadiusEntry 2 }

	configRadiusIpAddress OBJECT-TYPE
		SYNTAX OCTET STRING MAX-ACCESS read-write STATUS current
		DESCRIPTION "Radius IPv4 address"
		::= { configRadiusEntry 3 }

	configRadiusPort OBJECT-TYPE
		SYNTAX INTEGER MAX-ACCESS read-write STATUS current
		DESCRIPTION "Radius UDP port"
		::= { configRadiusEntry 4 }

	configRadiusSecret OBJECT-TYPE
		SYNTAX OCTET STRING MAX-ACCESS read-write STATUS current
		DESCRIPTION "Radius shared secret"
		::= { configRadiusEntry 5 }
-- Table - Radius servers }

configDetailsNasId OBJECT-TYPE
	SYNTAX OCTET STRING(SIZE(0..48))
	MAX-ACCESS read-write STATUS current
	DESCRIPTION "NAS identifier for the RADIUS servers
		    [FW:E2148.AC.1:2.8.0.1]"
	::= { netdetails 2 }

-- Table FilterGroup {
configFilterGroupTable OBJECT-TYPE
	SYNTAX SEQUENCE OF ConfigFilterGroupEntry
	MAX-ACCESS not-accessible
	STATUS current
	DESCRIPTION
		"List of filter group.
		[FW:E2148.AC.1:2.8.0.1]"
	::= { netdetails 3 }

configFilterGroupEntry OBJECT-TYPE
	SYNTAX ConfigFilterGroupEntry
	MAX-ACCESS not-accessible
	STATUS current
	DESCRIPTION
		"Details about a filter group
		[FW:E2148.AC.1:2.8.0.1]"
	INDEX { configFilterGroupIndex }
	::= { configFilterGroupTable 1 }

-- Elements in the filter group table

	ConfigFilterGroupEntry ::=
	    SEQUENCE {
			configFilterGroupIndex OCTET STRING
			,configFilterGroupRowStatus RowStatus
			,configFilterGroupFriendlyName OCTET STRING
		}

	configFilterGroupIndex OBJECT-TYPE
		SYNTAX OCTET STRING MAX-ACCESS read-write STATUS current
		DESCRIPTION "filter group index"
		::= { configFilterGroupEntry 1 }

	configFilterGroupRowStatus OBJECT-TYPE
		SYNTAX RowStatus MAX-ACCESS read-create STATUS current
		DESCRIPTION "row addition/deletion support
		[PF:fgroup_:1]"
		::= { configFilterGroupEntry 2 }

	configFilterGroupFriendlyName OBJECT-TYPE
		SYNTAX OCTET STRING MAX-ACCESS read-write STATUS current
		DESCRIPTION "Filter group friendly name (as displayed in the web UI)"
		::= { configFilterGroupEntry 3 }

-- Table FilterGroup }

-- Table FilterGroupRule {
configFilterGroupRuleTable OBJECT-TYPE
	SYNTAX SEQUENCE OF ConfigFilterGroupRuleEntry
	MAX-ACCESS not-accessible
	STATUS current
	DESCRIPTION
		"List of filter group rules.
		[FW:E2148.AC.1:2.8.0.1]"
	::= { netdetails 4 }

configFilterGroupRuleEntry OBJECT-TYPE
	SYNTAX ConfigFilterGroupRuleEntry
	MAX-ACCESS not-accessible
	STATUS current
	DESCRIPTION
		"Details about a filter rule
		[FW:E2148.AC.1:2.8.0.1]"
	INDEX { configFilterGroupRuleIndex }
	::= { configFilterGroupRuleTable 1 }

	-- Elements in the filter group rule table

	ConfigFilterGroupRuleEntry ::=
	    SEQUENCE {
			configFilterGroupRuleIndex OCTET STRING
			,configFilterGroupRuleRowStatus RowStatus
			,configFilterGroupGroupIndex OCTET STRING
			,configFilterGroupRuleMACFrameType INTEGER
			,configFilterGroupRuleCheckMAC INTEGER
			,configFilterGroupRuleNetworkProtocol INTEGER
			,configFilterGroupRuleIpAddress IpAddress
			,configFilterGroupRuleNetmask IpAddress
			,configFilterGroupRuleCheckIP INTEGER
			,configFilterGroupRuleTransportProtocol INTEGER
			,configFilterGroupRuleFirstPort INTEGER
			,configFilterGroupRuleLastPort INTEGER
			,configFilterGroupRuleCheckPort INTEGER
		}

	configFilterGroupRuleIndex OBJECT-TYPE
		SYNTAX OCTET STRING MAX-ACCESS read-write STATUS current
		DESCRIPTION "filter group rule index"
		::= { configFilterGroupRuleEntry 1 }

	configFilterGroupRuleRowStatus OBJECT-TYPE
		SYNTAX RowStatus MAX-ACCESS read-create STATUS current
		DESCRIPTION "row addition/deletion support
		[PF:frule_:1]"
		::= { configFilterGroupRuleEntry 2 }

	configFilterGroupGroupIndex OBJECT-TYPE
		SYNTAX OCTET STRING MAX-ACCESS read-write STATUS current
		DESCRIPTION "Filter group to which the rule belongs to"
		::= { configFilterGroupRuleEntry 3 }

	configFilterGroupRuleMACFrameType OBJECT-TYPE
		SYNTAX INTEGER {
			nofilter(1)
			,unicast(2)
			,broadcast(3)
			,multicast(4)
			,invalid(-255)
		}
		MAX-ACCESS read-write STATUS current
		DESCRIPTION "Type of frame"
		::= { configFilterGroupRuleEntry 4 }

	configFilterGroupRuleCheckMAC OBJECT-TYPE
		SYNTAX INTEGER {
			source(1)
			,destination(2)
			,invalid(-255)
		}
		MAX-ACCESS read-write STATUS current
		DESCRIPTION "frame MAC field to check"
		::= { configFilterGroupRuleEntry 5 }

	configFilterGroupRuleNetworkProtocol OBJECT-TYPE
		SYNTAX INTEGER {
			nofilter(-1)
			,ip(-2)
			,arp(-3)
			,invalid(-255)
		}
		MAX-ACCESS read-write STATUS current
		DESCRIPTION "Network protocol. nofilter(-1), IP(-2), ARP(-3), (&gt;0) for
			custom protocol. IP and ARP are shortcuts for 2048 (0x800) and
			2054 (0x806)
			-255: invalid value"
		::= { configFilterGroupRuleEntry 6 }

	configFilterGroupRuleIpAddress OBJECT-TYPE
		SYNTAX IpAddress MAX-ACCESS read-write STATUS current
		DESCRIPTION "Group rule filter IP address."
		::= { configFilterGroupRuleEntry 7 }

	configFilterGroupRuleNetmask OBJECT-TYPE
		SYNTAX IpAddress MAX-ACCESS read-write STATUS current
		DESCRIPTION "Group rule filter netmask."
		::= { configFilterGroupRuleEntry 8 }

	configFilterGroupRuleCheckIP OBJECT-TYPE
		SYNTAX INTEGER {
			source(1)
			,destination(2)
			,invalid(-255)
		}
		MAX-ACCESS read-write STATUS current
		DESCRIPTION "IP frame field to check"
		::= { configFilterGroupRuleEntry 9 }

	configFilterGroupRuleTransportProtocol OBJECT-TYPE
		SYNTAX INTEGER {
			nofilter(1)
			,udp(2)
			,tcp(3)
			,icmp(4)
			,invalid(-255)
		}
		MAX-ACCESS read-write STATUS current
		DESCRIPTION "Type of transport protocol"
		::= { configFilterGroupRuleEntry 10 }

	configFilterGroupRuleFirstPort OBJECT-TYPE
		SYNTAX INTEGER (1..65535) MAX-ACCESS read-write STATUS current
		DESCRIPTION "Lower bound of port selection
		-255: invalid value"
		::= { configFilterGroupRuleEntry 11 }

	configFilterGroupRuleLastPort OBJECT-TYPE
		SYNTAX INTEGER (1..65535) MAX-ACCESS read-write STATUS current
		DESCRIPTION "Upper bound of port selection
		-255: invalid value"
		::= { configFilterGroupRuleEntry 12 }

	configFilterGroupRuleCheckPort OBJECT-TYPE
		SYNTAX INTEGER {
			source(1),
			destination(2),
			invalid(-255)
		} MAX-ACCESS read-write STATUS current
		DESCRIPTION "Transport field to check"
		::= { configFilterGroupRuleEntry 13 }

-- Table FilterGroupRule }

-- Table - Network interfaces {

configInterfaceTable OBJECT-TYPE
	SYNTAX SEQUENCE OF ConfigInterfaceEntry
	MAX-ACCESS not-accessible STATUS current
	DESCRIPTION "List of network interfaces currently defined. The interfaces are defined by firmware.
		    [FW:E2148.AC.1:2.8.0.1]"
	::= { netif 2 }

configInterfaceEntry OBJECT-TYPE
	SYNTAX ConfigInterfaceEntry
	MAX-ACCESS not-accessible STATUS current
	DESCRIPTION "Details about a network interface
		    [FW:E2148.AC.1:2.8.0.1]"
	INDEX { configInterfaceName }
	::= { configInterfaceTable 1 }

	-- Elements in the IP subnet status table

	ConfigInterfaceEntry ::=
	    SEQUENCE {
			configInterfaceName NetifName, -- br-lan, wlanX, ethX.Y...
			configInterfaceRowStatus RowStatus,
			configInterfaceType INTEGER,
			configInterfaceDepends NetifName,
			configInterfaceOutputFilterGroup OCTET STRING,
			configInterfaceFilterGroupDir INTEGER,
			configInterfaceInputFilterGroup OCTET STRING
		}

	configInterfaceName OBJECT-TYPE
		SYNTAX NetifName
		MAX-ACCESS read-only STATUS current
		DESCRIPTION "Symbolic name of the interface.
			Referenced in masters and slave interfaces."
		::= { configInterfaceEntry 1 }

	configInterfaceRowStatus OBJECT-TYPE
		SYNTAX RowStatus MAX-ACCESS read-create STATUS current
		DESCRIPTION "row addition/deletion support
		[MAX-ACCESS:read-only]"
		::= { configInterfaceEntry 2 }

	configInterfaceType OBJECT-TYPE
		SYNTAX INTEGER {
			ethernet(1) ,mac-bridge(2) ,wifi-sta(3)
			,wifi-ap(4) ,wifi-11s(5) ,wifi-rept(6)
			,wifi-adhoc(7) ,vlan8021q(8), l2tunnel-gre(9)
			,wifi-srcc(10), cellular(11), mac-bond(12)
			,wifi-monitor(13)
			-- ,vpn(14)
			}
		MAX-ACCESS read-only STATUS current
		DESCRIPTION "Interface type: eth, AP, wifi client..."
		::= { configInterfaceEntry 3 }

	configInterfaceDepends OBJECT-TYPE
		SYNTAX NetifName
		MAX-ACCESS read-write STATUS current
		DESCRIPTION "The master interface this interface belongs to.
		Only the bridge type interface can be displayed and configured here.
		For the ipSubnet type interface which this interface depends to, please see configIpSubnetTable.
		This OID is not yet available for L2 GRE tunnel mode."
		::= { configInterfaceEntry 4 }

	configInterfaceOutputFilterGroup OBJECT-TYPE
		SYNTAX OCTET STRING
		MAX-ACCESS read-write STATUS current
		DESCRIPTION "The output filter group this interface belongs to.
			Please refer to configFilterGroupTable and configFilterGroupRuleTable in order to check or change filter group in this interface.
			The filter is used only if this interface is bridged.
			"
		::= { configInterfaceEntry 5 }

	configInterfaceFilterGroupDir OBJECT-TYPE
		SYNTAX INTEGER {
			none(0),
			in(1),
			out(2),
			inout(3)
		}
		MAX-ACCESS read-write STATUS obsolete
		DESCRIPTION "The filter group traffic direction.
			Attention: This OID is obsolete."
		::= { configInterfaceEntry 6 }

	configInterfaceInputFilterGroup OBJECT-TYPE
		SYNTAX OCTET STRING
		MAX-ACCESS read-write STATUS current
		DESCRIPTION "The input filter group this interface belongs to.
			Please refer to configFilterGroupTable and configFilterGroupRuleTable in order to check or change filter group in this interface.
			The filter is used only if this interface is bridged.
			[FW:E2148.AC.1:3.12.9.1]
			"
		::= { configInterfaceEntry 7 }

-- Table - Network interfaces }

-- Table - Ethernet ports {
--
--configEthernetTable OBJECT-TYPE
--	SYNTAX SEQUENCE OF ConfigEthernetEntry
--	MAX-ACCESS not-accessible STATUS current
--	DESCRIPTION "List of Ethernets interfaces"
--	::= { netif 6 }
--
--configEthernetEntry OBJECT-TYPE
--	SYNTAX ConfigEthernetEntry
--	MAX-ACCESS not-accessible STATUS current
--	DESCRIPTION "Details about an Ethernet network interface"
--	INDEX { configEthernetName }
--	::= { configEthernetTable 1 }
--
	-- Elements in the IP subnet status table
--
--	ConfigEthernetEntry ::=
--	    SEQUENCE {
--			,configEthernetName NetifName - - eth0
--			,configEthernetLabel OCTET STRING
			--,configEthernetVlan OCTET STRING - - futur: ingress tagging
--		}
--
--	configEthernetName OBJECT-TYPE
--		SYNTAX NetifName
--		MAX-ACCESS read-only STATUS current
--		DESCRIPTION "Symbolic name of the Ethernet port.
--			Referred to in the general Interfaces table."
--		::= { configEthernetEntry 1 }
--
--	configEthernetLabel OBJECT-TYPE
--		SYNTAX DisplayString
--		MAX-ACCESS read-only STATUS current
--		DESCRIPTION "The label physically identifying the port on the device"
--		::= { configEthernetEntry 2 }
-- Table - Ethernet ports }

-- Tables - Wi-Fi clients {

configIfStaTable OBJECT-TYPE
	SYNTAX SEQUENCE OF ConfigIfStaEntry
	MAX-ACCESS not-accessible STATUS current
	DESCRIPTION "List of Wi-Fi client connections currently defined
		    [FW:E2148.AC.1:2.8.0.1]"
	::= { netif 3 }

configIfStaEntry OBJECT-TYPE
	SYNTAX ConfigIfStaEntry
	MAX-ACCESS not-accessible STATUS current
	DESCRIPTION "Details about a Wi-Fi service set
		    [FW:E2148.AC.1:2.8.0.1]"
	INDEX { configIfStaName }
	::= { configIfStaTable 1 }

	-- Wlan elements when in STA mode

	ConfigIfStaEntry ::=
	    SEQUENCE {
			configIfStaName NetifName -- phy0wl0
			,configIfStaRowStatus RowStatus
			,configIfStaPhy NetifName

			,configIfStaSsid OCTET STRING
			,configIfStaBssid PhysAddress
			,configIfStaBridgingMode INTEGER

			-- == roaming info == --
			,configIfStaScanChannels OCTET STRING
			,configIfStaScanPassive INTEGER
			,configIfStaRoamingEnable DisableEnable
			,configIfStaRoamingEnableDBM INTEGER
			,configIfStaRoamingRequiredBoost INTEGER
			,configIfStaRoamingScanPeriod INTEGER

			-- == security info (Part 1) == --
			,configIfStaSecurityMode INTEGER
			,configIfStaWepKey1 WepKeys
			,configIfStaWepKey2 WepKeys
			,configIfStaWepKey3 WepKeys
			,configIfStaWepKey4 WepKeys
			,configIfStaWepKey INTEGER
			,configIfStaWpaVersion WpaVersions
			,configIfStaWpaCipher CipherTypes
			,configIfStaIdentity OCTET STRING
			,configIfStaKey OCTET STRING
			,configIfStaPrivateKey OCTET STRING
			,configIfStaCACert OCTET STRING
			,configIfStaEapType INTEGER
			,configIfStaAuthentication PeapSecurityProtocol
			,configIfStaFastBSSTransitionActivated DisableEnable
			,configIfStaIgnorePreviousScansResults DisableEnable
			,configIfStaRoamingRssiSmoothingFactor INTEGER
			,configIfStaRoamingBeaconTimeout INTEGER
			,configIfStaWpaKeyCacheLifetime INTEGER

			-- == advanced roaming == --
			,configIfStaRoamingCurrentApScanThreshold INTEGER
			,configIfStaRoamingMinimumStaLevel INTEGER
			,configIfStaRoamingAboveLevelThreshold INTEGER
			,configIfStaRoamingMaxSignalLevel INTEGER
			,configIfStaRoamingMinRoamDelay INTEGER
			,configIfStaRoamingNoReturnDelay INTEGER
			,configIfStaRoamingThresholdHysteresis INTEGER
			,configIfStaRoamingOffChanMaxDelay INTEGER
			,configIfStaRoamingOffChanProbeDelay INTEGER
			,configIfStaRoamingPerChanProbeDelay INTEGER

			-- == security info (Part 2) == --
			,configIfStaUserCert OCTET STRING

			-- == advanced info == --
			,configIfStaDeauthBeforeRoamingtoNextAP DisableEnable

		}

	configIfStaName OBJECT-TYPE
		SYNTAX NetifName
		MAX-ACCESS read-only STATUS current
		DESCRIPTION "Symbolic name of the wlan.
			 Referred to in the general Interfaces table."
		::= { configIfStaEntry 1 }

	configIfStaRowStatus OBJECT-TYPE
		SYNTAX RowStatus MAX-ACCESS read-create STATUS current
		DESCRIPTION "row addition/deletion support
		[radio]"
		::= { configIfStaEntry 2 }

	configIfStaPhy OBJECT-TYPE
		SYNTAX NetifName
		MAX-ACCESS read-only STATUS current
		DESCRIPTION "PHY index for this wlan"
		::= { configIfStaEntry 3 }

	configIfStaSsid OBJECT-TYPE
		SYNTAX OCTET STRING(SIZE(0..32))
		MAX-ACCESS read-write STATUS current
		DESCRIPTION "SSID string"
		::= { configIfStaEntry 4 }

	configIfStaBssid OBJECT-TYPE
		SYNTAX PhysAddress MAX-ACCESS read-write STATUS current
		DESCRIPTION "Not implemented yet
		[MAX-ACCESS:read-only]"
		::= { configIfStaEntry 5 }

	configIfStaBridgingMode OBJECT-TYPE
		SYNTAX INTEGER {
			arpnat(1)
			,four-addresses(2)
			,mono-eth-cloning(3)
			,mono-profinet-clonning(4)
			,multi-eth-cloning(5)
			}
		MAX-ACCESS read-write STATUS current
		DESCRIPTION "Bridging mode."
		::= { configIfStaEntry 6 }

	configIfStaScanChannels OBJECT-TYPE
		SYNTAX OCTET STRING MAX-ACCESS read-write STATUS current
		DESCRIPTION "List of radio frequencies (in MHz) scanned for the next AP discovery:
		Ignored if roaming is disabled.
		"
		::= { configIfStaEntry 7 }

	configIfStaScanPassive OBJECT-TYPE
		SYNTAX DisableEnable MAX-ACCESS read-write STATUS current
		DESCRIPTION "Not implemented yet
		[MAX-ACCESS:read-only]"
		::= { configIfStaEntry 8 }

	configIfStaRoamingEnable OBJECT-TYPE
		SYNTAX DisableEnable MAX-ACCESS read-write STATUS current
		DESCRIPTION "Global fast-handover/roaming function activation"
		::= { configIfStaEntry 9 }

	configIfStaRoamingEnableDBM OBJECT-TYPE
		SYNTAX INTEGER MAX-ACCESS read-write STATUS current
		DESCRIPTION "Roaming is allowed when current AP signal
			drops below this level (negative value, e.g. -60)"
		::= { configIfStaEntry 10 }

	configIfStaRoamingRequiredBoost OBJECT-TYPE
		SYNTAX INTEGER MAX-ACCESS read-write STATUS current
		DESCRIPTION "Roaming occurs only if the candidate signal
			level is above the current AP's plus this value"
		::= { configIfStaEntry 11 }

	configIfStaRoamingScanPeriod OBJECT-TYPE
		SYNTAX INTEGER MAX-ACCESS read-write STATUS current
		DESCRIPTION "Background scan period when roaming is enabled"
		::= { configIfStaEntry 12 }

	configIfStaSecurityMode OBJECT-TYPE
		SYNTAX SecurityModes
		MAX-ACCESS read-write STATUS current
		DESCRIPTION "Security policy"
		::= { configIfStaEntry 13 }

	configIfStaWepKey1 OBJECT-TYPE
		SYNTAX WepKeys MAX-ACCESS read-write STATUS current
		DESCRIPTION "WEP key 1 in hexadecimal format"
		::= { configIfStaEntry 14 }

	configIfStaWepKey2 OBJECT-TYPE
		SYNTAX WepKeys MAX-ACCESS read-write STATUS current
		DESCRIPTION "WEP key 2 in hexadecimal format"
		::= { configIfStaEntry 15 }

	configIfStaWepKey3 OBJECT-TYPE
		SYNTAX WepKeys MAX-ACCESS read-write STATUS current
		DESCRIPTION "WEP key 3 in hexadecimal format"
		::= { configIfStaEntry 16 }

	configIfStaWepKey4 OBJECT-TYPE
		SYNTAX WepKeys MAX-ACCESS read-write STATUS current
		DESCRIPTION "WEP key 4 in hexadecimal format"
		::= { configIfStaEntry 17 }

	configIfStaWepKey OBJECT-TYPE
		SYNTAX INTEGER MAX-ACCESS read-write STATUS current
		DESCRIPTION "WEP key slot selected: a value between 1 and 4 that indicates select one of the four WEP keys
		Ignored if configIfStaSecurityMode is different than wep."
		::= { configIfStaEntry 18 }

	configIfStaWpaVersion OBJECT-TYPE
		SYNTAX WpaVersions MAX-ACCESS read-write STATUS current
		DESCRIPTION "WPA version.
		Ignored if configIfStaSecurityMode is different than wpa-*."
		::= { configIfStaEntry 19 }

	configIfStaWpaCipher OBJECT-TYPE
		SYNTAX CipherTypes MAX-ACCESS read-only STATUS current
		DESCRIPTION "WPA cipher:
		WPA mode supports only TKIP(1).
		WPA2 mode supports only AES(2).
		Mixed WPA/WPA2 mode supports only AESTKIP(3).
		WPA3 mode supports only AES(2).
		Mixed WP2/WPA3 mode supports only AES(2).
		Ignored if configIfStaSecurityMode is different than wpa-*.
		[FW:E2148.AC.1:3.12.10.1]"
		::= { configIfStaEntry 20 }

	configIfStaIdentity OBJECT-TYPE
		SYNTAX OCTET STRING MAX-ACCESS read-write STATUS current
		DESCRIPTION "User ID (PEAP, TTLS)"
		::= { configIfStaEntry 21 }

	configIfStaKey OBJECT-TYPE
		SYNTAX OCTET STRING MAX-ACCESS read-write STATUS current
		DESCRIPTION "User password or WPA-PSK passphrase (or
			WPA 64-hex key) or TLS private key password"
		::= { configIfStaEntry 22 }

	configIfStaPrivateKey OBJECT-TYPE
		SYNTAX OCTET STRING MAX-ACCESS read-write STATUS current
		DESCRIPTION "TLS private key.
			A GET for this OID returns a string whose first
			byte is '1' if the key was uploaded, else '0'"
		::= { configIfStaEntry 23 }

	configIfStaCACert OBJECT-TYPE
		SYNTAX OCTET STRING MAX-ACCESS read-write STATUS current
		DESCRIPTION "EAP certificate.
			A GET for this OID returns a string whose first
			byte is '1' if the key was uploaded, else '0'"
		::= { configIfStaEntry 24 }

	configIfStaEapType OBJECT-TYPE
		SYNTAX INTEGER { eap-tls(1), eap-peap(2), eap-leap(3) }
		MAX-ACCESS read-write STATUS current
		DESCRIPTION "EAP type; eap-peap is the same as eap-ttls"
		::= { configIfStaEntry 25 }

	configIfStaAuthentication OBJECT-TYPE
		SYNTAX PeapSecurityProtocol
		MAX-ACCESS read-write STATUS current
		DESCRIPTION "Authentication type for phase 2"
		::= { configIfStaEntry 26 }

	configIfStaFastBSSTransitionActivated OBJECT-TYPE
		SYNTAX DisableEnable
		MAX-ACCESS read-write STATUS current
		DESCRIPTION "802.11r support (dot11FastBSSTransitionActivated):
		802.11r supports only client mode with all WPA/WPA2 policies."
		::= { configIfStaEntry 27 }

	configIfStaIgnorePreviousScansResults OBJECT-TYPE
		SYNTAX DisableEnable
		MAX-ACCESS read-write STATUS current
		DESCRIPTION "When scanning for APs, ignore those APs found prior to the
			last scan pass"
		::= { configIfStaEntry 28 }

	configIfStaRoamingRssiSmoothingFactor OBJECT-TYPE
		SYNTAX INTEGER
		MAX-ACCESS read-write STATUS current
		DESCRIPTION "RSSI smoothing factor
			The RSSI of the current AP is computed over the last few beacons received.
			Select the importance of the last beacon relative to older ones:
			the RSSI smoothing factor is a value between 1 and 16 that indicates the step of 1/16 (e.g. 3/16, 5/16 or 16/16)
			It is expressed in percentage format in WEB interface:
			6%(1), 13%(2), 19%(3), 25%(4),
			31%(5), 38%(6), 44%(7), 50%(8),
			56%(9), 63%(10), 69%(11), 75%(12),
			81%(13), 88%(14), 94%(15), 100%(16)

			Default: 19%(3)
			Ignored if roaming is disabled."
		::= { configIfStaEntry 29 }

	configIfStaRoamingBeaconTimeout OBJECT-TYPE
		SYNTAX INTEGER
		MAX-ACCESS read-write STATUS current
		DESCRIPTION "Beacon timeout:
		Value in beacon interval unit."
		::= { configIfStaEntry 30 }

	configIfStaWpaKeyCacheLifetime OBJECT-TYPE
		SYNTAX INTEGER
		MAX-ACCESS read-write STATUS current
		DESCRIPTION "Expressed in seconds."
		::= { configIfStaEntry 31 }

	configIfStaRoamingCurrentApScanThreshold OBJECT-TYPE
		SYNTAX INTEGER
		MAX-ACCESS read-write STATUS current
		DESCRIPTION "In dBm, e.g. '-75'. Above (better than) this value, the
			device will stop scanning. Set to 0 to scan unconditionally.
			Incompatible with the Maximum signal level option."
		::= { configIfStaEntry 32 }

	configIfStaRoamingMinimumStaLevel OBJECT-TYPE
		SYNTAX INTEGER
		MAX-ACCESS read-write STATUS current
		DESCRIPTION "In dBm, e.g. '-75'. 0 to disable. Roaming won't occur if
			the candidate signal is below this level. Association is still
			possible if no other AP is available."
		::= { configIfStaEntry 33 }

	configIfStaRoamingAboveLevelThreshold OBJECT-TYPE
		SYNTAX INTEGER
		MAX-ACCESS read-write STATUS current
		DESCRIPTION "In dBm, e.g. '-30'. Leave empty or 0 to disable. Roaming
			will occur when the current AP signal crosses and exceeds this
			value, and there is an acceptable candidate around. This allows
			elimination of approaching AP antennas that will be soon overtaken."
		::= { configIfStaEntry 34 }

	configIfStaRoamingMaxSignalLevel OBJECT-TYPE
		SYNTAX INTEGER
		MAX-ACCESS read-write STATUS current
		DESCRIPTION "In dBm, e.g. '-30'. Leave empty or 0 to disable. Must be
			greater or equal to the 'Excessive signal detection threshold'.
			Roaming will occur whenever the current AP signal is above this
			value, and there is an acceptable candidate around. When selecting
			the next AP, the ones above this value are considered last."
		::= { configIfStaEntry 35 }

	configIfStaRoamingMinRoamDelay OBJECT-TYPE
		SYNTAX INTEGER
		MAX-ACCESS read-write STATUS current
		DESCRIPTION "In ms. Leave empty or 0 to disable. Roaming won't occur
			before this delay has elapsed since the last association."
		::= { configIfStaEntry 36 }

	configIfStaRoamingNoReturnDelay OBJECT-TYPE
		SYNTAX INTEGER
		MAX-ACCESS read-write STATUS current
		DESCRIPTION "In ms. Leave empty or 0 to disable, max 180000 (3 mn).
			Roaming won't occur to an AP that was left recently (before this
			delay gos elapsed). The delay is cleared for APs that are not around
			anymore."
		::= { configIfStaEntry 37 }

	configIfStaRoamingThresholdHysteresis OBJECT-TYPE
		SYNTAX INTEGER
		MAX-ACCESS read-write STATUS current
		DESCRIPTION "Value in dBm, e.g. '2'. Hysteresis used for all thresholds.
			This value will be added and substracted to each threshold to set
			the corresponding threshold hysteresis interval."
		::= { configIfStaEntry 38 }

	configIfStaRoamingOffChanMaxDelay OBJECT-TYPE
		SYNTAX INTEGER
		MAX-ACCESS read-write STATUS current
		DESCRIPTION "In ms. Maximum delay offchannel (during which data must be
			buffered by the associated AP). Channels will be scanned without
			returning to the base channel, until this delay is exhausted.
			This value will be trimmed to the beacon interval of the AP."
		::= { configIfStaEntry 39 }

	configIfStaRoamingOffChanProbeDelay OBJECT-TYPE
		SYNTAX INTEGER
		MAX-ACCESS read-write STATUS current
		DESCRIPTION "In ms. Delay for collision avoidance after a channel switch,
			before sending the probe request."
		::= { configIfStaEntry 40 }

	configIfStaRoamingPerChanProbeDelay OBJECT-TYPE
		SYNTAX INTEGER
		MAX-ACCESS read-write STATUS current
		DESCRIPTION "In ms. Time to wait for an answer from the access points."
		::= { configIfStaEntry 41 }

	configIfStaUserCert OBJECT-TYPE
		SYNTAX OCTET STRING MAX-ACCESS read-write STATUS current
		DESCRIPTION "EAP User certificate.
			A GET for this OID returns a string whose first
			byte is '1' if the key was uploaded, else '0'"
		::= { configIfStaEntry 42 }

	configIfStaDeauthBeforeRoamingtoNextAP OBJECT-TYPE
		SYNTAX DisableEnable MAX-ACCESS read-write STATUS current
		DESCRIPTION "Deauthenticate before roaming to next AP.
			Write 2 (Enable), the previous AP stops transmission immediately, saving up bandwidth.
			Write 1 (Disable), let more time for the AP controller to manager handover.
			[FW:E2148.AC.1:3.16.0.1]"
		::= { configIfStaEntry 43 }

-- Tables - Wi-Fi clients }

-- Tables - Access points {

configIfAPTable OBJECT-TYPE
	SYNTAX SEQUENCE OF ConfigIfAPEntry
	MAX-ACCESS not-accessible STATUS current
	DESCRIPTION "Access point services table
		    [FW:E2148.AC.1:2.8.0.1]"
	::= { netif 4 }

configIfAPEntry OBJECT-TYPE
	SYNTAX ConfigIfAPEntry
	MAX-ACCESS not-accessible STATUS current
	DESCRIPTION "Access point services details
		    [FW:E2148.AC.1:2.8.0.1]"
	INDEX { configIfAPName }
	::= { configIfAPTable 1 }

	-- Wlan elements when in AP mode

	ConfigIfAPEntry ::=
	    SEQUENCE {
			configIfAPName NetifName -- radioXwY
			,configIfAPRowStatus RowStatus
			,configIfAPPhy NetifName -- radioX

			,configIfAPSsid OCTET STRING
			,configIfAPHidden INTEGER
			,configIfAPWds INTEGER
			,configIfAPIsolate INTEGER
			-- dtim, beacon_int, basic_rate, supported_rate
			-- mac filter
			--,configIfAPBssid PhysAddress - - a ajouter plus tard
			--,configIfAPChannel INTEGER - - voir radio

			-- == security info == --
			,configIfAPSecurityMode SecurityModes
			,configIfAPWepKey1 WepKeys
			,configIfAPWepKey2 WepKeys
			,configIfAPWepKey3 WepKeys
			,configIfAPWepKey4 WepKeys
			,configIfAPWepKey INTEGER
			,configIfAPWepAuthentication INTEGER
			,configIfAPWpaVersion WpaVersions
			,configIfAPWpaCipher CipherTypes
			,configIfAPKey OCTET STRING
			,configIfAPRadiusIndex INTEGER
			,configIfAPPreAuthentication DisableEnable
			,configIfAPMACFilterBehaviour INTEGER
			,configIfAPMACFilterAddresses OCTET STRING
			,configIfAPWpaGroupRekey INTEGER
			,configIfAPWpaPairRekey INTEGER
			,configIfAPWpaMasterRekey INTEGER
			,configIfAPWpaProtectedFrame INTEGER
			,configIfAPMaxSimultaneousAssoc INTEGER

			-- == Passpoint == --
			,configIfAPPasspointConfigName OCTET STRING
		}

	configIfAPName OBJECT-TYPE
		SYNTAX NetifName
		MAX-ACCESS read-only STATUS current
		DESCRIPTION "Symbolic name of the wlan.
			Referred to in the general Interfaces table."
		::= { configIfAPEntry 1 }

	configIfAPRowStatus OBJECT-TYPE
		SYNTAX RowStatus MAX-ACCESS read-create STATUS current
		DESCRIPTION "row addition/deletion support
		[radio]"
		::= { configIfAPEntry 2 }

	configIfAPPhy OBJECT-TYPE
		SYNTAX NetifName
		MAX-ACCESS read-only STATUS current
		DESCRIPTION "PHY index for this wlan"
		::= { configIfAPEntry 3 }

	configIfAPSsid OBJECT-TYPE
		SYNTAX OCTET STRING(SIZE(0..32))
		MAX-ACCESS read-write STATUS current
		DESCRIPTION "SSID string"
		::= { configIfAPEntry 4 }

	configIfAPHidden OBJECT-TYPE
		SYNTAX DisableEnable MAX-ACCESS read-write STATUS current
		DESCRIPTION "Do not broadcast SSID"
		::= { configIfAPEntry 5 }

	configIfAPWds OBJECT-TYPE
		SYNTAX DisableEnable MAX-ACCESS read-write STATUS current
		DESCRIPTION "Enable WDS (4-addresses) stations support"
		::= { configIfAPEntry 6 }

	configIfAPIsolate OBJECT-TYPE
		SYNTAX DisableEnable MAX-ACCESS read-write STATUS current
		DESCRIPTION "Isolate clients from eachother"
		::= { configIfAPEntry 7 }

	configIfAPSecurityMode OBJECT-TYPE
		SYNTAX SecurityModes MAX-ACCESS read-write STATUS current
		DESCRIPTION "Security policy"
		::= { configIfAPEntry 8 }

	configIfAPWepKey1 OBJECT-TYPE
		SYNTAX WepKeys MAX-ACCESS read-write STATUS current
		DESCRIPTION "WEP key 1 in hexadecimal format"
		::= { configIfAPEntry 9 }

	configIfAPWepKey2 OBJECT-TYPE
		SYNTAX WepKeys MAX-ACCESS read-write STATUS current
		DESCRIPTION "WEP key 2 in hexadecimal format"
		::= { configIfAPEntry 10 }

	configIfAPWepKey3 OBJECT-TYPE
		SYNTAX WepKeys MAX-ACCESS read-write STATUS current
		DESCRIPTION "WEP key 3 in hexadecimal format"
		::= { configIfAPEntry 11 }

	configIfAPWepKey4 OBJECT-TYPE
		SYNTAX WepKeys MAX-ACCESS read-write STATUS current
		DESCRIPTION "WEP key 4 in hexadecimal format"
		::= { configIfAPEntry 12 }

	configIfAPWepKey OBJECT-TYPE
		SYNTAX INTEGER MAX-ACCESS read-write STATUS current
		DESCRIPTION "WEP key slot selected: a value between 1 and 4 that indicates select one of the four WEP keys.
		Ignored if configIfAPSecurityMode is different than wep."
		::= { configIfAPEntry 13 }

	configIfAPWepAuthentication OBJECT-TYPE
		SYNTAX INTEGER { open(1), shared(2) }
		MAX-ACCESS read-write STATUS current
		DESCRIPTION "Set WEP Authentication"
		::= { configIfAPEntry 14 }

	configIfAPWpaVersion OBJECT-TYPE
		SYNTAX WpaVersions MAX-ACCESS read-write STATUS current
		DESCRIPTION "WPA version.
		Ignored if configIfAPSecurityMode is different than wpa-*."
		::= { configIfAPEntry 15 }

	configIfAPWpaCipher OBJECT-TYPE
		SYNTAX CipherTypes MAX-ACCESS read-only STATUS current
		DESCRIPTION "WPA cipher:
		WPA mode supports only TKIP(1).
		WPA2 mode supports only AES(2).
		WPA3 mode supports only AES(2).
		Mixed WPA/WPA2 mode supports only AESTKIP(3).
		Mixed WPA2/WPA3 mode supports only AES(2).
		Ignored if configIfApSecurityMode is different than wpa-*.
		[FW:E2148.AC.1:3.12.10.1]"
		::= { configIfAPEntry 16 }

	configIfAPKey OBJECT-TYPE
		SYNTAX OCTET STRING(SIZE(8..64))
		MAX-ACCESS read-write STATUS current
		DESCRIPTION "WPA key:
		In wpa-wpa2-psk security mode, this key is pre-shared key;
		In wpa-wpa3-psk security mode, this key is pre-shared key;
		In wpa-wpa2 (eap) security mode, this key is shared secret;
		In wpa-wpa3 (eap) security mode, this key is shared secret;"
		::= { configIfAPEntry 17 }

	configIfAPRadiusIndex OBJECT-TYPE
		SYNTAX INTEGER MAX-ACCESS read-write STATUS current
		DESCRIPTION "RADIUS table entry index"
		::= { configIfAPEntry 18 }

	configIfAPPreAuthentication OBJECT-TYPE
		SYNTAX DisableEnable MAX-ACCESS read-write STATUS current
		DESCRIPTION "Enable / Disable pre-authentication"
		::= { configIfAPEntry 19 }

	configIfAPMACFilterBehaviour OBJECT-TYPE
		SYNTAX INTEGER{
			disabled(1)
			,denyMAC(2)
			,allowMAC(3)
		} MAX-ACCESS read-write STATUS current
		DESCRIPTION "MAC address filter mode"
		::= { configIfAPEntry 20 }

	configIfAPMACFilterAddresses OBJECT-TYPE
		SYNTAX OCTET STRING MAX-ACCESS read-write STATUS current
		DESCRIPTION "MAC filter addresses separated by comas"
		::= { configIfAPEntry 21 }

	configIfAPWpaGroupRekey OBJECT-TYPE
		SYNTAX INTEGER MAX-ACCESS read-write STATUS current
		DESCRIPTION "Time interval for rekeying the WPA GTK in second"
		::= { configIfAPEntry 22 }

	configIfAPWpaPairRekey OBJECT-TYPE
		SYNTAX INTEGER MAX-ACCESS read-write STATUS current
		DESCRIPTION "Time interval for rekeying the WPA PTK in second"
		::= { configIfAPEntry 23 }

	configIfAPWpaMasterRekey OBJECT-TYPE
		SYNTAX INTEGER MAX-ACCESS read-write STATUS current
		DESCRIPTION "Time interval for rekeying the WPA GMK in second"
		::= { configIfAPEntry 24 }

	configIfAPWpaProtectedFrame OBJECT-TYPE
		SYNTAX INTEGER{
			disabled(1)
			,enable-optional(2)
			,enable-required(3)
		} MAX-ACCESS read-write STATUS current
		DESCRIPTION "Protected management frame:
					Set for preventing a hacker DoS attack.
					Ignored if configIfApSecurityMode is different than wpa-*.
					By default, the management frames are not protected.
					[FW:E2148.AC.1:3.12.9.1]"
		::= { configIfAPEntry 25 }

	configIfAPMaxSimultaneousAssoc OBJECT-TYPE
		SYNTAX INTEGER MAX-ACCESS read-write STATUS current
		DESCRIPTION "The maximum number of clients allowed to connect on the AP.
					-1 indicates invalid value.
					[FW:E2148.AC.1:3.12.9.1]"
		::= { configIfAPEntry 26 }

	configIfAPPasspointConfigName OBJECT-TYPE
		SYNTAX OCTET STRING
		MAX-ACCESS read-write STATUS current
		DESCRIPTION "Applied Passpoint config name.
					Empty name means Passpoint not activated.
					[FW:E2148.AC.1:X.XX.X.X]"
		::= { configIfAPEntry 27 }

-- Tables - Access points }

-- Tables - Wi-Fi mesh points {

configIfMeshTable OBJECT-TYPE
	SYNTAX SEQUENCE OF ConfigIfMeshEntry
	MAX-ACCESS not-accessible STATUS current
	DESCRIPTION "List of 802.11s mesh interfaces currently defined
		    [FW:E2148.AC.1:2.8.0.1]"
	::= { netif 5 }

configIfMeshEntry OBJECT-TYPE
	SYNTAX ConfigIfMeshEntry
	MAX-ACCESS not-accessible STATUS current
	DESCRIPTION "Details about a 802.11s network
     		    [FW:E2148.AC.1:2.8.0.1]"
	INDEX { configIfMeshName }
	::= { configIfMeshTable 1 }

	-- Wlan elements when in Mesh mode

	ConfigIfMeshEntry ::=
	    SEQUENCE {
			configIfMeshName NetifName -- phy0wl0
			,configIfMeshRowStatus RowStatus
			,configIfMeshPhy NetifName

			,configIfMeshId OCTET STRING

			-- == security info == --
			,configIfMeshSecurityMode INTEGER
			,configIfMeshPreSharedKey OCTET STRING
			-- == advanced configuration
			,configIfMeshPathRefreshTime INTEGER
			,configIfMeshMinDiscoveryTimeout INTEGER
			,configIfMeshActivePathTimeout INTEGER
			,configIfMeshNetworkDiameterTraversalTime INTEGER
			,configIfMeshRootMode INTEGER
			,configIfMeshGatesAnnouncement DisableEnable
			,configIfMeshActivePathToRootTimeout INTEGER
			,configIfMeshPreqRootInterval INTEGER
			,configIfMeshRannRootInterval INTEGER
		}

	configIfMeshName OBJECT-TYPE
		SYNTAX NetifName
		MAX-ACCESS read-only STATUS current
		DESCRIPTION "Symbolic name of the wlan.
			Referred to in the general Interfaces table."
		::= { configIfMeshEntry 1 }

	configIfMeshRowStatus OBJECT-TYPE
		SYNTAX RowStatus MAX-ACCESS read-create STATUS current
		DESCRIPTION "row addition/deletion support
		[radio]"
		::= { configIfMeshEntry 2 }

	configIfMeshPhy OBJECT-TYPE
		SYNTAX NetifName
		MAX-ACCESS read-only STATUS current
		DESCRIPTION "PHY index for this wlan"
		::= { configIfMeshEntry 3 }

	configIfMeshId OBJECT-TYPE
		SYNTAX OCTET STRING(SIZE(0..32))
		MAX-ACCESS read-write STATUS current
		DESCRIPTION "Mesh ID string"
		::= { configIfMeshEntry 4 }

	configIfMeshSecurityMode OBJECT-TYPE
		SYNTAX INTEGER {
			none(1),
			sae(5)
		}
		MAX-ACCESS read-write STATUS current
		DESCRIPTION "Security policy"
		::= { configIfMeshEntry 5 }

	configIfMeshPreSharedKey OBJECT-TYPE
		SYNTAX OCTET STRING(SIZE(8..64)) MAX-ACCESS read-write STATUS current
		DESCRIPTION "SAE preshared key. Ignored if configIfMeshSecurityMode is
					different than sae."
		::= { configIfMeshEntry 6 }

	configIfMeshPathRefreshTime OBJECT-TYPE
		SYNTAX INTEGER
		MAX-ACCESS read-write STATUS current
		DESCRIPTION "Mesh paths refresh interval (in ms)"
		::= { configIfMeshEntry 7 }

	configIfMeshMinDiscoveryTimeout OBJECT-TYPE
		SYNTAX INTEGER
		MAX-ACCESS read-write STATUS current
		DESCRIPTION "Mesh min discovery timeout (in ms)"
		::= { configIfMeshEntry 8 }

	configIfMeshActivePathTimeout OBJECT-TYPE
		SYNTAX INTEGER
		MAX-ACCESS read-write STATUS current
		DESCRIPTION "Mesh active path timeout (in ms)"
		::= { configIfMeshEntry 9 }

	configIfMeshNetworkDiameterTraversalTime OBJECT-TYPE
		SYNTAX INTEGER
		MAX-ACCESS read-write STATUS current
		DESCRIPTION "Duration of a there and back again trough the mesh network
			(in TUs). 1 TU = 1024us"
		::= { configIfMeshEntry 10 }

	configIfMeshRootMode OBJECT-TYPE
		SYNTAX INTEGER {
			notroot(1)
			,proactivepreq(2)
			,proactivepreqprep(3)
			,proactiverann(4)
		}
		MAX-ACCESS read-write STATUS current
		DESCRIPTION "Mesh root mode."
		::= { configIfMeshEntry 11 }

	configIfMeshGatesAnnouncement OBJECT-TYPE
		SYNTAX DisableEnable
		MAX-ACCESS read-write STATUS current
		DESCRIPTION "Enable / disable gates announcements. In case mesh root
			mode is different than not_root"
		::= { configIfMeshEntry 12 }

	configIfMeshActivePathToRootTimeout OBJECT-TYPE
		SYNTAX INTEGER
		MAX-ACCESS read-write STATUS current
		DESCRIPTION "Mesh active path to root timeout (in TUs) (1 TU = 1024us).
			In case mesh root mode is proactive_preq or proactive_preq_prep"
		::= { configIfMeshEntry 13 }

	configIfMeshPreqRootInterval OBJECT-TYPE
		SYNTAX INTEGER
		MAX-ACCESS read-write STATUS current
		DESCRIPTION "Mesh preq root interval (in TUs) (1 TU = 1024us).
			In case mesh root mode is proactive_preq or proactive_preq_prep"
		::= { configIfMeshEntry 14 }

	configIfMeshRannRootInterval OBJECT-TYPE
		SYNTAX INTEGER
		MAX-ACCESS read-write STATUS current
		DESCRIPTION "Mesh RANN root interval (in TUs) (1 TU = 1024us).
			In case mesh root mode is proactive_rann"
		::= { configIfMeshEntry 15 }

-- Tables - Wi-Fi mesh points }

-- Tables - MAC bridge (software switch) {

configIfBridgeTable OBJECT-TYPE
	SYNTAX SEQUENCE OF ConfigIfBridgeEntry
	MAX-ACCESS not-accessible STATUS current
	DESCRIPTION "List of MAC bridges modules currently defined
		    [FW:E2148.AC.1:2.8.0.1]"
	::= { netif 6 }

configIfBridgeEntry OBJECT-TYPE
	SYNTAX ConfigIfBridgeEntry
	MAX-ACCESS not-accessible STATUS current
	DESCRIPTION "Details about a MAC bridge
		    [FW:E2148.AC.1:2.8.0.1]"
	INDEX { configIfBridgeName }
	::= { configIfBridgeTable 1 }

	-- Bridge elements

	ConfigIfBridgeEntry ::=
	    SEQUENCE {
			configIfBridgeName NetifName -- lan
			,configIfBridgeRowStatus RowStatus
			,configIfBridgeStp INTEGER
			,configIfBridgePriority INTEGER
			,configIfBridgeHello INTEGER
			,configIfBridgeMaxAge INTEGER
			,configIfBridgeForwardDelay INTEGER
			,configIfBridgeLldpForward DisableEnable
		}

	configIfBridgeName OBJECT-TYPE
		SYNTAX NetifName
		MAX-ACCESS read-only STATUS current
		DESCRIPTION "Symbolic name of the MAC bridge.
			Referred to in the general Interfaces table."
		::= { configIfBridgeEntry 1 }

	configIfBridgeRowStatus OBJECT-TYPE
		SYNTAX RowStatus MAX-ACCESS read-create STATUS current
		DESCRIPTION "row addition/deletion support"
		::= { configIfBridgeEntry 2 }

	configIfBridgeStp OBJECT-TYPE
		SYNTAX INTEGER {off(1),rstp(2),stp-only(3)}
		MAX-ACCESS read-write STATUS current
		DESCRIPTION "1 disables RSTP, 2 sets to automatic RSTP/STP
			determination, 3 enforces legacy STP"
		::= { configIfBridgeEntry 3 }

	configIfBridgePriority OBJECT-TYPE
		SYNTAX INTEGER MAX-ACCESS read-write STATUS current
		DESCRIPTION "(R)STP bridge priority"
		::= { configIfBridgeEntry 4 }

	configIfBridgeHello OBJECT-TYPE
		SYNTAX INTEGER MAX-ACCESS read-write STATUS current
		DESCRIPTION "(R)STP hello interval"
		::= { configIfBridgeEntry 5 }

	configIfBridgeMaxAge OBJECT-TYPE
		SYNTAX INTEGER MAX-ACCESS read-write STATUS current
		DESCRIPTION "(R)STP max age"
		::= { configIfBridgeEntry 6 }

	configIfBridgeForwardDelay OBJECT-TYPE
		SYNTAX INTEGER MAX-ACCESS read-write STATUS current
		DESCRIPTION "(R)STP forward delay"
		::= { configIfBridgeEntry 7 }

	configIfBridgeLldpForward OBJECT-TYPE
		SYNTAX DisableEnable MAX-ACCESS read-write STATUS current
		DESCRIPTION "Enables the LLDP frame forwarding. Required for
			profinet device cloning"
		::= { configIfBridgeEntry 8 }
-- Tables - MAC bridge (software switch) }

configIfVlanTable OBJECT-TYPE
	SYNTAX SEQUENCE OF ConfigIfVlanEntry
	MAX-ACCESS not-accessible STATUS current
	DESCRIPTION "List of MAC Vlan modules currently defined
		    [FW:E2148.AC.1:2.8.0.1]"
	::= { netif 7 }

configIfVlanEntry OBJECT-TYPE
	SYNTAX ConfigIfVlanEntry
	MAX-ACCESS not-accessible STATUS current
	DESCRIPTION "Details about a MAC Vlan
		    [FW:E2148.AC.1:2.8.0.1]"
	INDEX { configIfVlanIndex }
	::= { configIfVlanTable 1 }

	ConfigIfVlanEntry ::=
	    SEQUENCE {
			configIfVlanIndex OCTET STRING
			,configIfVlanRowStatus RowStatus
			,configIfVlanFriendlyName OCTET STRING
			,configIfVlanHostIfName NetifName
			,configIfVlanId INTEGER
		}

	configIfVlanIndex OBJECT-TYPE
		SYNTAX OCTET STRING MAX-ACCESS read-write STATUS current
		DESCRIPTION "Vlan name"
		::= { configIfVlanEntry 1 }

	configIfVlanRowStatus OBJECT-TYPE
		SYNTAX RowStatus MAX-ACCESS read-create STATUS current
		DESCRIPTION "row addition/deletion support
		[PF:vlan:1]"
		::= { configIfVlanEntry 2 }

	configIfVlanFriendlyName OBJECT-TYPE
		SYNTAX OCTET STRING MAX-ACCESS read-write STATUS current
		DESCRIPTION "VLAN friendly name"
		::= { configIfVlanEntry 3 }

	configIfVlanHostIfName OBJECT-TYPE
		SYNTAX NetifName MAX-ACCESS read-write STATUS current
		DESCRIPTION "MAC Host interface"
		::= { configIfVlanEntry 4 }

	configIfVlanId OBJECT-TYPE
		SYNTAX INTEGER MAX-ACCESS read-write STATUS current
		DESCRIPTION "Vlan Id"
		::= { configIfVlanEntry 5 }

-- Tables - SRCC {

configIfSrccTable OBJECT-TYPE
	SYNTAX SEQUENCE OF ConfigIfSrccEntry
	MAX-ACCESS not-accessible STATUS current
	DESCRIPTION "List of SRCC connections currently defined.
				[FW:E2148.AC.1:3.12.9.1]"
	::= { netif 8 }

configIfSrccEntry OBJECT-TYPE
	SYNTAX ConfigIfSrccEntry
	MAX-ACCESS not-accessible STATUS current
	DESCRIPTION "List of SRCC connections currently defined.
				[FW:E2148.AC.1:3.12.9.1]"
	INDEX { configIfSrccName }
	::= { configIfSrccTable 1 }

	-- Wlan elements when in SRCC mode

	ConfigIfSrccEntry ::=
	    SEQUENCE {
			configIfSrccName NetifName
			,configIfSrccRowStatus RowStatus
			,configIfSrccPhy NetifName
			,configIfSrccDiscoverApSsid OCTET STRING
			,configIfSrccProductType INTEGER
			,configIfSrccDiscSigThreshold INTEGER
			,configIfSrccDiscDuration INTEGER
			,configIfSrccBrokenThreshold INTEGER
			,configIfSrccBrokenDuration INTEGER
			,configIfSrccWifiBand INTEGER
			,configIfSrccFirstChannel INTEGER
			,configIfSrccSecondChannel INTEGER
			,configIfSrccDiscScanDuration INTEGER
			,configIfSrccMixRedundancy INTEGER
			,configIfSrccMixRedundancyBoost INTEGER
			,configIfSrccPeerTableTimeout INTEGER
			,configIfSrccTargetTableTimeout INTEGER
			,configIfSrccPeerAcknowTimeout INTEGER
			,configIfSrccPeerReconfigTimeout INTEGER
			,configIfSrccGreBridgeIpAddr IpAddress
		}

	configIfSrccName OBJECT-TYPE
		SYNTAX NetifName
		MAX-ACCESS read-only STATUS current
		DESCRIPTION "Symbolic name of the wlan.
			Referred to in the general Interfaces table."
		::= { configIfSrccEntry 1 }

	configIfSrccRowStatus OBJECT-TYPE
		SYNTAX RowStatus MAX-ACCESS read-create STATUS current
		DESCRIPTION "Row addition/deletion support
		[radio]"
		::= { configIfSrccEntry 2 }

	configIfSrccPhy OBJECT-TYPE
		SYNTAX NetifName
		MAX-ACCESS read-only STATUS current
		DESCRIPTION "PHY index for this wlan."
		::= { configIfSrccEntry 3 }

	configIfSrccDiscoverApSsid OBJECT-TYPE
		SYNTAX OCTET STRING(SIZE(0..32))
		MAX-ACCESS read-write STATUS current
		DESCRIPTION "SRCC SSID string for discovering the other potential partners."
		::= { configIfSrccEntry 4 }

	configIfSrccProductType OBJECT-TYPE
		SYNTAX INTEGER {typeA(1),typeB(2)}
		MAX-ACCESS read-write STATUS current
		DESCRIPTION "The devices on the same coach edge must have the same type.
					-1 indicates invalid value."
		::= { configIfSrccEntry 5 }

	configIfSrccDiscSigThreshold OBJECT-TYPE
		SYNTAX INTEGER MAX-ACCESS read-write STATUS current
		DESCRIPTION "Link establishment threshold in dBm. By default, the value is -50.
					A potential partner is valid if its signal level stays over
					Link establishment threshold during more than the Link establishment duration.
					Consider the OID configIfSrccDiscDuration."
		::= { configIfSrccEntry 6 }

	configIfSrccDiscDuration OBJECT-TYPE
		SYNTAX INTEGER MAX-ACCESS read-write STATUS current
		DESCRIPTION "Link establishment duration in seconds. By default, the value is 60.
					A potential partner is considered valid if its signal level stays over
					Link establishment threshold during more than the Link establishment duration.
					Consider the OID configIfSrccDiscSigThreshold."
		::= { configIfSrccEntry 7 }

	configIfSrccBrokenThreshold OBJECT-TYPE
		SYNTAX INTEGER MAX-ACCESS read-write STATUS current
		DESCRIPTION "Broken link threshold in dBm. By default, the value is -70.
					The established link is considered broken if its signal drops below
					Broken link threshold during more than Broken Link duration.
					Consider the OID configIfSrccBrokenDuration."
		::= { configIfSrccEntry 8 }

	configIfSrccBrokenDuration OBJECT-TYPE
		SYNTAX INTEGER MAX-ACCESS read-write STATUS current
		DESCRIPTION "Broken link duration in seconds. By default, the value is 660.
					The established link is considered broken if its signal drops below
					Broken link threshold during more than Broken Link duration.
					Consider the OID configIfSrccBrokenThreshold."
		::= { configIfSrccEntry 9 }

	configIfSrccWifiBand OBJECT-TYPE
		SYNTAX INTEGER {band-5g(1), band-24(2)}
		MAX-ACCESS read-write STATUS current
		DESCRIPTION "The WiFi frequency range fo the final links.
					band-5g (1) for the 5GHz and band-24 (2) for the 2.4GHz.
					-1 indicates invalid value."
		::= { configIfSrccEntry 10 }

	configIfSrccFirstChannel OBJECT-TYPE
		SYNTAX INTEGER MAX-ACCESS read-write STATUS current
		DESCRIPTION "The wireless channel associated with the first SRCC final link.
					-1 indicates invalid value."
		::= { configIfSrccEntry 11 }

	configIfSrccSecondChannel OBJECT-TYPE
		SYNTAX INTEGER MAX-ACCESS read-write STATUS current
		DESCRIPTION "The wireless channel associated with the first SRCC final link.
					-1 indicates invalid value."
		::= { configIfSrccEntry 12 }

	configIfSrccDiscScanDuration OBJECT-TYPE
		SYNTAX INTEGER MAX-ACCESS read-write STATUS current
		DESCRIPTION "The global duration in seconds of the Ethernet topology discovery scan.
					By default, the value is 120."
		::= { configIfSrccEntry 13 }

	configIfSrccMixRedundancy OBJECT-TYPE
		SYNTAX INTEGER {wifi(1), ethernet(2), none(3)}
		MAX-ACCESS read-write STATUS current
		DESCRIPTION "Redundancy method.
					1: Wifi+Wifi
					2: Wifi+Ethernet
					3: Wifi alone (not redundant)
		[SYNFW:3:E2148.AC.1:4.10.0.1]."
		::= { configIfSrccEntry 14 }

	configIfSrccMixRedundancyBoost OBJECT-TYPE
		SYNTAX INTEGER MAX-ACCESS read-write STATUS current
		DESCRIPTION "Gain in percent added to the target metric.
					Minimum = 1; maximum = 65535. By default, the value is 40."
		::= { configIfSrccEntry 15 }

	configIfSrccPeerTableTimeout OBJECT-TYPE
		SYNTAX INTEGER MAX-ACCESS read-write STATUS current
		DESCRIPTION "Peer table timeout in seconds: the wireless discover timeout for a partner(peer).
					By default, the value is 20."
		::= { configIfSrccEntry 16 }

	configIfSrccTargetTableTimeout OBJECT-TYPE
		SYNTAX INTEGER MAX-ACCESS read-write STATUS current
		DESCRIPTION "Target table timeout in seconds: the wireless discover timeout for
					the whole cell(the group of wireless peers). By default, the value is 120."
		::= { configIfSrccEntry 17 }

	configIfSrccPeerAcknowTimeout OBJECT-TYPE
		SYNTAX INTEGER MAX-ACCESS read-write STATUS current
		DESCRIPTION "The duration in seconds the Master waits for the answer from all
					partners after sending its proposed cell architecture.
					By default, the value is 120."
		::= { configIfSrccEntry 18 }

	configIfSrccPeerReconfigTimeout OBJECT-TYPE
		SYNTAX INTEGER MAX-ACCESS read-write STATUS current
		DESCRIPTION "The duration in seconds the Master waits for all the partners to
					switch to their final roles. By default, the value is 200."
		::= { configIfSrccEntry 19 }

	configIfSrccGreBridgeIpAddr OBJECT-TYPE
		SYNTAX IpAddress MAX-ACCESS read-write STATUS current
		DESCRIPTION "Internal L2 GRE interface IP prefix represents the GRE interface IP prefix.
					SRCC's internal uses a GRE L2 tunnel, in which the interface is configured with a C class IPV4 address.
					The netmask for this ip network is 255.255.255.0. Thus the first 3 octets only are meaningful.
					The last digit replace with 1 if the final role is AP; with 2 if the final role is client."
		::= { configIfSrccEntry 20 }

-- Tables - SRCC }

-- Table GRE Tunnel L2 {
-- Put here GRE L2 settings
-- Table GRE Tunnel L2 }

-- Tables - IP subnets {
configIpSubnetTable OBJECT-TYPE
	SYNTAX SEQUENCE OF ConfigIpSubnetEntry
	MAX-ACCESS not-accessible
	STATUS current
	DESCRIPTION
		"List of network interfaces currently associated
		with an IP address
		[FW:E2148.AC.1:2.8.0.1]"
	::= { tcpip 1 }

configIpSubnetEntry OBJECT-TYPE
	SYNTAX ConfigIpSubnetEntry
	MAX-ACCESS not-accessible
	STATUS current
	DESCRIPTION
		"Details about an IP address
		[FW:E2148.AC.1:2.8.0.1]"
	INDEX { configIpSubnetName }
	::= { configIpSubnetTable 1 }

	-- Elements in the IP subnet status table

	ConfigIpSubnetEntry ::=
	    SEQUENCE {
			configIpSubnetName NetifName
			,configIpSubnetRowStatus RowStatus
			,configIpAddressMode INTEGER
			,configIpSubnetIPv4Addr IpAddress
			,configIpSubnetIPv4Mask IpAddress
			,configIpSubnetMetric INTEGER
			,configIpSubnetDnsList OCTET STRING
			,configIpSubnetInterface OCTET STRING
			,configIpSubnetIPv4Gateway IpAddress
			,configIpSubnetFriendlyName OCTET STRING
			,configIpSubnetBridgeEnable DisableEnable
			,configIpSubnetPersistence TriState
			,configIpSubnetAutoStart TriState
			,configIpSubnetEnable DisableEnable
			,configIpSubnetPeerDns DisableEnable
			,configIpSubnetDefaultRoute DisableEnable
		}

	configIpSubnetName OBJECT-TYPE
		SYNTAX NetifName
		MAX-ACCESS read-only STATUS current
		DESCRIPTION "Interface attached to this subnet"
		::= { configIpSubnetEntry 1 }

	configIpSubnetRowStatus OBJECT-TYPE
		SYNTAX RowStatus MAX-ACCESS read-create STATUS current
		DESCRIPTION "row addition/deletion support
		[net]"
		::= { configIpSubnetEntry 2 }

	configIpAddressMode OBJECT-TYPE
		SYNTAX INTEGER {static(1),dhcp(2),none(3),vrrp(4)}
		MAX-ACCESS read-write STATUS current
		DESCRIPTION "Ip address protocol of this subnet"
		::= { configIpSubnetEntry 3 }

	configIpSubnetIPv4Addr OBJECT-TYPE
		SYNTAX IpAddress MAX-ACCESS read-write STATUS current
		DESCRIPTION "IPv4 address given to the interface"
		::= { configIpSubnetEntry 4 }

	configIpSubnetIPv4Mask OBJECT-TYPE
		SYNTAX IpAddress MAX-ACCESS read-write STATUS current
		DESCRIPTION "IPv4 subnet mask"
		::= { configIpSubnetEntry 5 }

	configIpSubnetMetric OBJECT-TYPE
		SYNTAX INTEGER MAX-ACCESS read-write STATUS current
		DESCRIPTION "Subnet metric"
		::= { configIpSubnetEntry 6 }

	configIpSubnetDnsList OBJECT-TYPE
		SYNTAX OCTET STRING
		MAX-ACCESS read-write STATUS current
		DESCRIPTION "Space-separated list of DNS IP addresses"
		::= { configIpSubnetEntry 7 }

	configIpSubnetInterface OBJECT-TYPE
		SYNTAX OCTET STRING
		MAX-ACCESS read-write STATUS current
		DESCRIPTION "Interface related to this ipSubnet. This field
			must be left blank for bridge interfaces"
		::= { configIpSubnetEntry 8 }

	configIpSubnetIPv4Gateway OBJECT-TYPE
		SYNTAX IpAddress MAX-ACCESS read-write STATUS current
		DESCRIPTION "IPv4 gateway"
		::= { configIpSubnetEntry 9 }

	configIpSubnetFriendlyName OBJECT-TYPE
		SYNTAX OCTET STRING MAX-ACCESS read-write STATUS current
		DESCRIPTION "Friendly name of this subnet"
		::= { configIpSubnetEntry 10 }

	configIpSubnetBridgeEnable OBJECT-TYPE
		SYNTAX DisableEnable
		MAX-ACCESS read-write STATUS current
		DESCRIPTION
		"Write 2 (Enable) to configure this subnet as a bridge type
		interface: create a bridge over specified interface(s) in this
		subnet.

		Write 1 (Disable) to configure this subnet as an IP subnet type
		interface: set IP settings to one specified interface.

		Warning: changing an interface type from bridge to IP subnet
		will delete the link between this bridge and all its interfaces."
		::= { configIpSubnetEntry 11 }

	configIpSubnetPersistence OBJECT-TYPE
		SYNTAX TriState MAX-ACCESS read-write STATUS current
		DESCRIPTION
		"Define the behaviour of the IP layer when the lower interface
		loses its connection.
		- When enabled, the IP settings (IP addresses, routes through
		  this interface...) remain in place.
		- When disabled, the IP settings are removed, possibly hanging
		  a tunnel or requiring a DHCP negotiation when the connection
		  recovers.
		- When set to default, follow the legacy behaviour i.e. enabled
		  for 'static' protocol configuration, disabled for 'dhcp'
		  configuration.
		[FW:E2148.AC.1:4.12.0.1]"
		::= { configIpSubnetEntry 12 }

	configIpSubnetEnable OBJECT-TYPE
		SYNTAX DisableEnable MAX-ACCESS read-write STATUS current
		DESCRIPTION
		"Set to Enable to install the layer 3 network. If disabled,
		this subnet will not be initialized (thus not useable) after
		the configuration is applied.
		[FW:E2148.AC.1:4.12.0.1]"
		::= { configIpSubnetEntry 13 }

	configIpSubnetAutoStart OBJECT-TYPE
		SYNTAX TriState MAX-ACCESS read-write STATUS current
		DESCRIPTION
		"Define whether, after installation and initialization, the
		subnet is activated immediately (when configuration is applied)
		or only when a suitable event happens. See the 'L3 network
		toggle' action in the Alarms/Events subsystem.

		'Enable' sets the subnet initially 'up', 'Disable' sets it
		initially 'down', 'Default' sets it initially 'up' except
		if configIpAddressMode=none.
		[FW:E2148.AC.1:4.12.0.1]"
		::= { configIpSubnetEntry 14 }

	configIpSubnetPeerDns OBJECT-TYPE
		SYNTAX DisableEnable MAX-ACCESS read-write STATUS current
		DESCRIPTION
		"If this subnet is a DHCP client, should the DNS obtained from
		the DHCP server replace the currently configured one?

		Set to 'Enable' to give preference to the DHCP-provided DNS.
		[FW:E2148.AC.1:4.12.0.1]"
		::= { configIpSubnetEntry 15 }

	configIpSubnetDefaultRoute OBJECT-TYPE
		SYNTAX DisableEnable MAX-ACCESS read-write STATUS current
		DESCRIPTION
		"If this subnet is a DHCP client, should the server-provided
		default route replace the currently configured one?

		Set to 'Enable' to give preference to the DHCP server route.
		[FW:E2148.AC.1:4.12.0.1]"
		::= { configIpSubnetEntry 16 }

-- Tables - IP subnets }

ipFactory OBJECT IDENTIFIER ::= { tcpip 2 }

-- Packet IpFactory
synfloodprotection OBJECT-TYPE
	SYNTAX DisableEnable
	MAX-ACCESS  read-write
    STATUS  current
    DESCRIPTION "Allow(2)/disallow(1) SYN flood protection.
		[FW:E2148.AC.1:2.8.0.1]"
    ::= { ipFactory 1 }

dropinvalidpacket OBJECT-TYPE
	SYNTAX DisableEnable
	MAX-ACCESS read-write
	STATUS current
	DESCRIPTION "Write 2(enable) to allow invalid packetdropping. Write
		1(disable) to disallow invalid packetdropping.
		[FW:E2148.AC.1:2.8.0.1]"
	::= { ipFactory 2 }

-- Table Zones {
configIpZonesTable OBJECT-TYPE
	SYNTAX SEQUENCE OF ConfigIpZonesEntry
	MAX-ACCESS not-accessible
	STATUS current
	DESCRIPTION
		"List of user defined network zones
		[FW:E2148.AC.1:2.8.0.1]"
	::= { ipFactory 3 }

configIpZonesEntry OBJECT-TYPE
	SYNTAX ConfigIpZonesEntry
	MAX-ACCESS not-accessible
	STATUS current
	DESCRIPTION
		"Details about an IpFactory Zone
		[FW:E2148.AC.1:2.8.0.1]"
	INDEX { configIpZoneIndex }
	::= { configIpZonesTable 1 }

	ConfigIpZonesEntry ::=
	    SEQUENCE {
			configIpZoneIndex OCTET STRING
			,configIpZoneRowStatus RowStatus
			,configIpZoneFriendlyName OCTET STRING
			,configIpZoneNAT DisableEnable
			,configIpZoneMSSClamping DisableEnable
			,configIpZoneDefaultAcceptancePolicy INTEGER
			,configIpZoneRestrictedAddressFamily INTEGER
			,configIpZoneConnectionTracking DisableEnable
			,configIpZoneLogging DisableEnable
			,configIpZoneLoggingLimit OCTET STRING
			,configIpZoneInterfaces OCTET STRING
		}

	configIpZoneIndex OBJECT-TYPE
		SYNTAX OCTET STRING
		MAX-ACCESS read-write STATUS current
		DESCRIPTION "Zone index"
		::= { configIpZonesEntry 1 }

	configIpZoneRowStatus OBJECT-TYPE
		SYNTAX RowStatus MAX-ACCESS read-create STATUS current
		DESCRIPTION "row addition/deletion support
			[PF:zone_:1]"
		::= { configIpZonesEntry 2 }

	configIpZoneFriendlyName OBJECT-TYPE
		SYNTAX OCTET STRING MAX-ACCESS read-write STATUS current
		DESCRIPTION "Friendly name"
		::= { configIpZonesEntry 3 }

	configIpZoneNAT OBJECT-TYPE
		SYNTAX DisableEnable MAX-ACCESS read-write STATUS current
		DESCRIPTION "Enable / Disable network address translation"
		::= { configIpZonesEntry 4 }

	configIpZoneMSSClamping OBJECT-TYPE
		SYNTAX DisableEnable MAX-ACCESS read-write STATUS current
		DESCRIPTION "Enable / Disable MSS Clamping"
		::= { configIpZonesEntry 5 }

	configIpZoneDefaultAcceptancePolicy OBJECT-TYPE
		SYNTAX INTEGER {
			allenable(1)
			,alldisable(2)
		} MAX-ACCESS read-write STATUS current
		DESCRIPTION "Default packet acceptance policy"
		::= { configIpZonesEntry 6 }

	configIpZoneRestrictedAddressFamily OBJECT-TYPE
		SYNTAX INTEGER {
			ipv4ipv6(1)
			,ipv4(2)
			,ipv6(3)
		} MAX-ACCESS read-write STATUS current
		DESCRIPTION "Restrict action on the given IP address family.
                     Attention:WaveOS supports only IPV4."
		::= { configIpZonesEntry 7 }

	configIpZoneConnectionTracking OBJECT-TYPE
		SYNTAX DisableEnable MAX-ACCESS read-write STATUS current
		DESCRIPTION "Enable / Disable connection tracking"
		::= { configIpZonesEntry 8 }

	configIpZoneLogging OBJECT-TYPE
		SYNTAX DisableEnable MAX-ACCESS read-write STATUS current
		DESCRIPTION "Enable / Disable logging for this zone"
		::= { configIpZonesEntry 9 }

	configIpZoneLoggingLimit OBJECT-TYPE
		SYNTAX OCTET STRING MAX-ACCESS read-write STATUS current
		DESCRIPTION
		"Defines the limit of logging messages per unit of time for
		this zone.
		This octet string is defined as : N[/T].
		Where N is the number of messages and T is one of:second,
		minute, hour or day. If the time unit (slash included) is
		not mentionned, /minute is used."
		::= { configIpZonesEntry 10 }

	configIpZoneInterfaces OBJECT-TYPE
		SYNTAX OCTET STRING MAX-ACCESS read-write STATUS current
		DESCRIPTION "The (space separated) interface list of network
				devices using this zone"
		::= { configIpZonesEntry 11 }

-- Table Zones }

-- Table traffic forwarding {
configIpNatIpForwardTable OBJECT-TYPE
	SYNTAX SEQUENCE OF ConfigIpNatIpForwardEntry
	MAX-ACCESS not-accessible
	STATUS current
	DESCRIPTION
		"List of IP forward rules, allows to redirect the input traffic on one zone to a device on private zone.
		Attention: This rule can be set when NAT is disabled but it's used only if NAT is enabled
		[FW:E2148.AC.1:2.8.0.1]"
	::= { ipFactory 4 }

configIpNatIpForwardEntry OBJECT-TYPE
	SYNTAX ConfigIpNatIpForwardEntry
	MAX-ACCESS not-accessible
	STATUS current
	DESCRIPTION
		"Details about an IP forward rule
		[FW:E2148.AC.1:2.8.0.1]"
	INDEX { configIpNatIpForwardIndex }
	::= { configIpNatIpForwardTable 1 }

	ConfigIpNatIpForwardEntry ::=
	    SEQUENCE {
			configIpNatIpForwardIndex OCTET STRING
			,configIpNatIpForwardRowStatus RowStatus
			,configIpNatIpForwardFriendlyName OCTET STRING
			,configIpNatIpForwardZoneName OCTET STRING
			,configIpNatIpForwardSrcIp IpAddress
			,configIpNatIpForwardProtocol INTEGER
			,configIpNatIpForwardPublicPort OCTET STRING
			,configIpNatIpForwardPrivatePort OCTET STRING
			,configIpNatIpForwardTargetIp IpAddress
		}

	configIpNatIpForwardIndex OBJECT-TYPE
		SYNTAX OCTET STRING
		MAX-ACCESS read-write STATUS current
		DESCRIPTION "IP forward rule index"
		::= { configIpNatIpForwardEntry 1 }

	configIpNatIpForwardRowStatus OBJECT-TYPE
		SYNTAX RowStatus MAX-ACCESS read-create STATUS current
		DESCRIPTION "row addition/deletion support
			[PF:rule_:1]"
		::= { configIpNatIpForwardEntry 2 }

	configIpNatIpForwardFriendlyName OBJECT-TYPE
		SYNTAX OCTET STRING MAX-ACCESS read-write STATUS current
		DESCRIPTION "Friendly name"
		::= { configIpNatIpForwardEntry 3 }

	configIpNatIpForwardZoneName OBJECT-TYPE
		SYNTAX OCTET STRING MAX-ACCESS read-write STATUS current
		DESCRIPTION "Zone this rule belongs to"
		::= { configIpNatIpForwardEntry 4 }

	configIpNatIpForwardSrcIp OBJECT-TYPE
		SYNTAX IpAddress MAX-ACCESS read-write STATUS current
		DESCRIPTION "Source IP"
		::= { configIpNatIpForwardEntry 5 }

	configIpNatIpForwardProtocol OBJECT-TYPE
		SYNTAX INTEGER {
			all(1)
			,tcp(2)
			,udp(3)
			,tcpudp(4)
			,icmp(5)
		} MAX-ACCESS read-write STATUS current
		DESCRIPTION "IP protocol"
		::= { configIpNatIpForwardEntry 6 }

	configIpNatIpForwardPublicPort OBJECT-TYPE
		SYNTAX OCTET STRING MAX-ACCESS read-write STATUS current
		DESCRIPTION "Public port"
		::= { configIpNatIpForwardEntry 7 }

	configIpNatIpForwardPrivatePort OBJECT-TYPE
		SYNTAX OCTET STRING MAX-ACCESS read-write STATUS current
		DESCRIPTION "Private port"
		::= { configIpNatIpForwardEntry 8 }

	configIpNatIpForwardTargetIp OBJECT-TYPE
		SYNTAX IpAddress MAX-ACCESS read-write STATUS current
		DESCRIPTION "The destination IP address"
		::= { configIpNatIpForwardEntry 9 }

-- Table traffic forwarding }

-- Table firewall {
configIpFirewallTable OBJECT-TYPE
	SYNTAX SEQUENCE OF ConfigIpFirewallEntry
	MAX-ACCESS not-accessible
	STATUS current
	DESCRIPTION
		"List of ip firewall rules on specified zone
		[FW:E2148.AC.1:2.8.0.1]"
	::= { ipFactory 5 }

configIpFirewallEntry OBJECT-TYPE
	SYNTAX ConfigIpFirewallEntry
	MAX-ACCESS not-accessible
	STATUS current
	DESCRIPTION
		"Details about an IP firewall rule
		[FW:E2148.AC.1:2.8.0.1]"
	INDEX { configIpFirewallIndex }
	::= { configIpFirewallTable 1 }

	ConfigIpFirewallEntry ::=
	    SEQUENCE {
			configIpFirewallIndex OCTET STRING
			,configIpFirewallRowStatus RowStatus
			,configIpFirewallZoneName OCTET STRING
			,configIpFirewallProtocol INTEGER
			,configIpFirewallPort OCTET STRING
			,configIpFirewallAction INTEGER
			,configIpFirewallDestZone OCTET STRING
			,configIpFirewallSrcIP IpAddress
			,configIpFirewallTargetIP IpAddress
		}

	configIpFirewallIndex OBJECT-TYPE
		SYNTAX OCTET STRING
		MAX-ACCESS read-write STATUS current
		DESCRIPTION "Ip forward rule index"
		::= { configIpFirewallEntry 1 }

	configIpFirewallRowStatus OBJECT-TYPE
		SYNTAX RowStatus MAX-ACCESS read-create STATUS current
		DESCRIPTION "row addition/deletion support
			[PF:rule_:1]"
		::= { configIpFirewallEntry 2 }

	configIpFirewallZoneName OBJECT-TYPE
		SYNTAX OCTET STRING MAX-ACCESS read-write STATUS current
		DESCRIPTION "Zone this rule belongs to"
		::= { configIpFirewallEntry 3 }

	configIpFirewallProtocol OBJECT-TYPE
		SYNTAX INTEGER {
			all(1)
			,tcp(2)
			,udp(3)
			,tcpudp(4)
			,icmp(5)
			,gre(6)
		}
		MAX-ACCESS read-write STATUS current
		DESCRIPTION "Transport protocol"
		::= { configIpFirewallEntry 4 }

	configIpFirewallPort OBJECT-TYPE
		SYNTAX OCTET STRING MAX-ACCESS read-write STATUS current
		DESCRIPTION "IP port"
		::= { configIpFirewallEntry 5 }

	configIpFirewallAction OBJECT-TYPE
		SYNTAX INTEGER {
			forward(1)
			,reject(2)
			,drop(3)
		}
		MAX-ACCESS read-write STATUS current
		DESCRIPTION "Action to take when the rule applies"
		::= { configIpFirewallEntry 6 }

	configIpFirewallDestZone OBJECT-TYPE
		SYNTAX OCTET STRING MAX-ACCESS read-write STATUS current
		DESCRIPTION "Destination zone. If left blank, local interface is
			selected."
		::= { configIpFirewallEntry 7 }

	configIpFirewallSrcIP OBJECT-TYPE
		SYNTAX IpAddress MAX-ACCESS read-write STATUS current
		DESCRIPTION "The source IP of this firewall rule
		[FW:E2148.AC.1:3.12.8.1]"
		::= { configIpFirewallEntry 8 }

	configIpFirewallTargetIP OBJECT-TYPE
		SYNTAX IpAddress MAX-ACCESS read-write STATUS current
		DESCRIPTION "The destination IP of this firewall rule
		[FW:E2148.AC.1:3.12.8.1]"
		::= { configIpFirewallEntry 9 }


-- Table firewall }

-- Table static rules {
configIpRoutesTable OBJECT-TYPE
	SYNTAX SEQUENCE OF ConfigIpRoutesEntry
	MAX-ACCESS not-accessible
	STATUS current
	DESCRIPTION
		"List of IP static routes
		[FW:E2148.AC.1:2.8.0.1]"
	::= { ipFactory 6 }

configIpRoutesEntry OBJECT-TYPE
	SYNTAX ConfigIpRoutesEntry
	MAX-ACCESS not-accessible
	STATUS current
	DESCRIPTION
		"Details about an IP static route
		[FW:E2148.AC.1:2.8.0.1]"
	INDEX { configIpRoutesIndex }
	::= { configIpRoutesTable 1 }

	ConfigIpRoutesEntry ::=
	    SEQUENCE {
			configIpRoutesIndex INTEGER
			,configIpRoutesRowStatus RowStatus
			,configIpRoutesNetwork OCTET STRING
			,configIpRoutesTarget IpAddress
			,configIpRoutesNetmask IpAddress
			,configIpRoutesGateway IpAddress
			,configIpRoutesMetric INTEGER
			,configIpRoutesMTU INTEGER
		}

	configIpRoutesIndex OBJECT-TYPE
		SYNTAX INTEGER
		MAX-ACCESS read-write STATUS current
		DESCRIPTION "Static route index"
		::= { configIpRoutesEntry 1 }

	configIpRoutesRowStatus OBJECT-TYPE
		SYNTAX RowStatus MAX-ACCESS read-create STATUS current
		DESCRIPTION "row addition/deletion support"
		::= { configIpRoutesEntry 2 }

	configIpRoutesNetwork OBJECT-TYPE
		SYNTAX OCTET STRING MAX-ACCESS read-write STATUS current
		DESCRIPTION "Network this rule is attached to"
		::= { configIpRoutesEntry 3 }

	configIpRoutesTarget OBJECT-TYPE
		SYNTAX IpAddress MAX-ACCESS read-write STATUS current
		DESCRIPTION "Target IP or network"
		::= { configIpRoutesEntry 4 }

	configIpRoutesNetmask OBJECT-TYPE
		SYNTAX IpAddress MAX-ACCESS read-write STATUS current
		DESCRIPTION "Target network. If target is a network"
		::= { configIpRoutesEntry 5 }

	configIpRoutesGateway OBJECT-TYPE
		SYNTAX IpAddress MAX-ACCESS read-write STATUS current
		DESCRIPTION "IP gateway"
		::= { configIpRoutesEntry 6 }

	configIpRoutesMetric OBJECT-TYPE
		SYNTAX INTEGER MAX-ACCESS read-write STATUS current
		DESCRIPTION "Packet metric"
		::= { configIpRoutesEntry 7 }

	configIpRoutesMTU OBJECT-TYPE
		SYNTAX INTEGER MAX-ACCESS read-write STATUS current
		DESCRIPTION "Packet MTU"
		::= { configIpRoutesEntry 8 }

-- Table static routes }

-- Table Zone Forward {
configIpZoneForwardTable OBJECT-TYPE
	SYNTAX SEQUENCE OF ConfigIpZoneForwardEntry
	MAX-ACCESS not-accessible
	STATUS current
	DESCRIPTION
		"List of zone forward rules
		[FW:E2148.AC.1:2.8.0.1]"
	::= { ipFactory 7 }

configIpZoneForwardEntry OBJECT-TYPE
	SYNTAX ConfigIpZoneForwardEntry
	MAX-ACCESS not-accessible
	STATUS current
	DESCRIPTION
		"Details about a zone forward rule
		[FW:E2148.AC.1:2.8.0.1]"
	INDEX { configIpZoneForwardIndex }
	::= { configIpZoneForwardTable 1 }

	ConfigIpZoneForwardEntry ::=
	    SEQUENCE {
			configIpZoneForwardIndex INTEGER
			,configIpZoneForwardSrc OCTET STRING
			,configIpZoneForwardDst OCTET STRING
			,configIpZoneForwardRowStatus RowStatus
		}

	configIpZoneForwardIndex OBJECT-TYPE
		SYNTAX INTEGER
		MAX-ACCESS read-write STATUS current
		DESCRIPTION "Zone forwarding index"
		::= { configIpZoneForwardEntry 1 }

	configIpZoneForwardRowStatus OBJECT-TYPE
		SYNTAX RowStatus MAX-ACCESS read-create STATUS current
		DESCRIPTION "row addition/deletion support"
		::= { configIpZoneForwardEntry 2 }

	configIpZoneForwardSrc OBJECT-TYPE
		SYNTAX OCTET STRING
		MAX-ACCESS read-write STATUS current
		DESCRIPTION "Source Zone"
		::= { configIpZoneForwardEntry 3 }

	configIpZoneForwardDst OBJECT-TYPE
		SYNTAX OCTET STRING
		MAX-ACCESS read-write STATUS current
		DESCRIPTION "Destination Zone"
		::= { configIpZoneForwardEntry 4 }

-- Table Zone Forward }

-- DSCP Tagging {

configIpDscpTaggingTable OBJECT-TYPE
	SYNTAX SEQUENCE OF ConfigIpDscpTaggingEntry
	MAX-ACCESS not-accessible
	STATUS current
	DESCRIPTION
		"List of DSCP tagging rules
		[FW:E2148.AC.1:2.8.0.1]"
	::= { ipFactory 8 }

configIpDscpTaggingEntry OBJECT-TYPE
	SYNTAX ConfigIpDscpTaggingEntry
	MAX-ACCESS not-accessible
	STATUS current
	DESCRIPTION
		"Details about a DSCP tagging rule
		[FW:E2148.AC.1:2.8.0.1]"
	INDEX { configIpDscpTaggingIndex }
	::= { configIpDscpTaggingTable 1 }

	ConfigIpDscpTaggingEntry ::=
	    SEQUENCE {
			configIpDscpTaggingIndex OCTET STRING
			,configIpDscpTaggingRowStatus RowStatus
			,configIpDscpTaggingFriendlyName OCTET STRING
			,configIpDscpTaggingProtocol INTEGER
			,configIpDscpTaggingSrcIP IpAddress
			,configIpDscpTaggingDstIP IpAddress
			,configIpDscpTaggingSrcPort OCTET STRING
			,configIpDscpTaggingDstPort OCTET STRING
			,configIpDscpTaggingDscpValue INTEGER
		}

	configIpDscpTaggingIndex OBJECT-TYPE
		SYNTAX OCTET STRING
		MAX-ACCESS read-write STATUS current
		DESCRIPTION "DSCP tagging rule index
		Enter a memonic name for this rule. Only letters, digits and underscores"
		::= { configIpDscpTaggingEntry 1 }

	configIpDscpTaggingRowStatus OBJECT-TYPE
		SYNTAX RowStatus MAX-ACCESS read-create STATUS current
		DESCRIPTION "row addition/deletion support"
		::= { configIpDscpTaggingEntry 2 }

	configIpDscpTaggingFriendlyName OBJECT-TYPE
		SYNTAX OCTET STRING MAX-ACCESS read-write STATUS current
		DESCRIPTION "Rule friendly name"
		::= { configIpDscpTaggingEntry 3 }

	configIpDscpTaggingProtocol OBJECT-TYPE
		SYNTAX INTEGER {
			all(1)
			,tcp(2)
			,udp(3)
			,icmp(4)
		}
		MAX-ACCESS read-write STATUS current
		DESCRIPTION "The protocol filter"
		::= { configIpDscpTaggingEntry 4 }

	configIpDscpTaggingSrcIP OBJECT-TYPE
		SYNTAX IpAddress MAX-ACCESS read-write STATUS current
		DESCRIPTION "The source IP filter"
		::= { configIpDscpTaggingEntry 5 }

	configIpDscpTaggingDstIP OBJECT-TYPE
		SYNTAX IpAddress MAX-ACCESS read-write STATUS current
		DESCRIPTION "The destination IP filter"
		::= { configIpDscpTaggingEntry 6 }

	configIpDscpTaggingSrcPort OBJECT-TYPE
		SYNTAX OCTET STRING MAX-ACCESS read-write STATUS current
		DESCRIPTION "The source port filter"
		::= { configIpDscpTaggingEntry 7 }

	configIpDscpTaggingDstPort OBJECT-TYPE
		SYNTAX OCTET STRING MAX-ACCESS read-write STATUS current
		DESCRIPTION "The destination port filter"
		::= { configIpDscpTaggingEntry 8 }

	configIpDscpTaggingDscpValue OBJECT-TYPE
		SYNTAX INTEGER MAX-ACCESS read-write STATUS current
		DESCRIPTION "The DSCP value applied by this rule"
		::= { configIpDscpTaggingEntry 9 }

-- DSCP Tagging }

-- Tables - IP routes {
--configIpRoutesTable OBJECT-TYPE
--	SYNTAX SEQUENCE OF ConfigIpRouteEntry
--	MAX-ACCESS not-accessible STATUS current
--	DESCRIPTION "List of configured IPv4 routes (NOT IMPLEMENTED YET)"
--	::= { tcpip 2 }
--
--configIpRouteEntry OBJECT-TYPE
--	SYNTAX ConfigIpRouteEntry
--	MAX-ACCESS not-accessible STATUS current
--	DESCRIPTION "Details about a configured IPv4 route"
	--INDEX { configIpSubnetIndex }
--	::= { configIpRoutesTable 1 }
--
	-- Elements in the IP routes configuration table
--
--	ConfigIpRouteEntry ::= SEQUENCE {
--		configRouteIndex INTEGER
--		,configIpRouteRowStatus RowStatus
--		,configRouteType INTEGER
--		,configRouteDest IpAddress
--		,configRouteNextHop IpAddress
--		,configRouteMask IpAddress
--	}
--
--	configRouteIndex OBJECT-TYPE
--		SYNTAX INTEGER MAX-ACCESS read-only STATUS current
--		DESCRIPTION "Route index"
--		::= { configIpRouteEntry 1 }
--
--	configRowStatus OBJECT-TYPE
--		SYNTAX RowStatus MAX-ACCESS read-create STATUS current
--		DESCRIPTION "row addition/deletion support"
--		::= { configEntry 2 }
--
--	configRouteType OBJECT-TYPE
--		SYNTAX INTEGER {host(1),net(2)}
--		MAX-ACCESS read-write STATUS current
--		DESCRIPTION "Route type"
--		::= { configIpRouteEntry 3 }
--
--	configRouteDest OBJECT-TYPE
--		SYNTAX IpAddress MAX-ACCESS read-write STATUS current
--		DESCRIPTION "IPv4 address of the target remote network"
--		::= { configIpRouteEntry 4 }
--
--	configRouteNextHop OBJECT-TYPE
--		SYNTAX IpAddress MAX-ACCESS read-write STATUS current
--		DESCRIPTION "Gateway used to communicate with the remote network"
--		::= { configIpRouteEntry 5 }
--
--	configRouteMask OBJECT-TYPE
--		SYNTAX IpAddress MAX-ACCESS read-write STATUS current
--		DESCRIPTION "Mask of  bits used in comparing candidate
--			addresses with destination"
--		::= { configIpRouteEntry 6 }
-- Table routes }

-- ====================================
-- roaming (dual interface fast handover) {
--

roamingAlgorithm OBJECT-TYPE
	SYNTAX INTEGER { none(0), scan(1), cbb(2), plh(3) }
	MAX-ACCESS read-write STATUS current
	DESCRIPTION "Dual interface handover method.
	None: the same radio interface scans and transfers data.
	Scan: one designated radio scans only, and the other transfers data.
	CBB (Connect Before Break): while a radio transfers data, the other
	^^^ scans and connects, to allow immediate traffic diversion.
	PLH (Predictive Linear Handover): variation of CBB where AP's are
	^^^ expected to line up, and direction of movement, therefore AP
	^^^ signal level slope, determines next AP to use.

	NOTE! setting this OID is as yet unsupported. Use the GUI instead.

	[FW:E2148.AC.1:4.12.0.1]"
	::= { roaming 1 }

roamingPLHposition OBJECT-TYPE
	SYNTAX INTEGER {front(1), rear(2)} MAX-ACCESS read-write STATUS current
	DESCRIPTION "Position of the antenna relative to vehicle motion.
	Front: the vehicle antenna moves closer to the target APs.
	Rear: the vehicle antenna moves away from the target APs.
	[FW:E2148.AC.1:4.12.0.1]"
	::= { roaming 2 }

roamingPLHjitter OBJECT-TYPE
	SYNTAX INTEGER (0..20) MAX-ACCESS read-write STATUS current
	DESCRIPTION
	"Minimum variation from highest sample to detect a slope
	direction change; e.g. 1 means detection needs at least 2 dB
	difference since the first 1dB is ignored.
	[FW:E2148.AC.1:4.12.0.1]"
	::= { roaming 3 }

roamingPLHurgent OBJECT-TYPE
	SYNTAX WifiLevel MAX-ACCESS read-write STATUS current DESCRIPTION
	"When the current AP is below this level and there is no
	candidate AP, the candidate selection rules are relaxed
	and the statusRoamingUrgent OID changes state.
	[FW:E2148.AC.1:4.12.0.1]"
	::= { roaming 4 }

roamingPLHfront OBJECT IDENTIFIER ::= { roaming 5 }

roamingPLHfrontCandMin OBJECT-TYPE
	SYNTAX WifiLevel MAX-ACCESS read-write STATUS current DESCRIPTION
	"Minimum signal level from an AP to select it as candidate
	target for a handover.
	[FW:E2148.AC.1:4.12.0.1]"
	::= { roamingPLHfront 1 }

roamingPLHfrontCandMax OBJECT-TYPE
	SYNTAX WifiLevel MAX-ACCESS read-write STATUS current DESCRIPTION
	"Maximum signal level from an AP to select it as candidate
	target for a handover.
	An AP above this is supposedly about to be bypassed and might
	fade quickly.
	[FW:E2148.AC.1:4.12.0.1]"
	::= { roamingPLHfront 2 }

roamingPLHfrontCurrentLow OBJECT-TYPE
	SYNTAX WifiLevel MAX-ACCESS read-write STATUS current DESCRIPTION
	"Signal level from the AP dedicated to data transfer, below
	which a handover to a candidate will be attempted.
	[FW:E2148.AC.1:4.12.0.1]"
	::= { roamingPLHfront 3 }

roamingPLHfrontCurrentHigh OBJECT-TYPE
	SYNTAX WifiLevel MAX-ACCESS read-write STATUS current DESCRIPTION
	"Signal level from the AP dedicated to data transfer, above
	which a handover to a candidate will be attempted.
	[FW:E2148.AC.1:4.12.0.1]"
	::= { roamingPLHfront 4 }

roamingPLHrear OBJECT IDENTIFIER ::= { roaming 6 }

roamingPLHrearCandMin OBJECT-TYPE
	SYNTAX WifiLevel MAX-ACCESS read-write STATUS current DESCRIPTION
	"Minimum signal level from an AP to select it as candidate
	target for a handover.
	[FW:E2148.AC.1:4.12.0.1]"
	::= { roamingPLHrear 1 }

roamingPLHrearCandMax OBJECT-TYPE
	SYNTAX WifiLevel MAX-ACCESS read-write STATUS current DESCRIPTION
	"Maximum signal level from an AP to select it as candidate
	target for a handover.
	An AP above this is supposedly about to be bypassed and might
	fade quickly.
	[FW:E2148.AC.1:4.12.0.1]"
	::= { roamingPLHrear 2 }

roamingPLHrearCurrentLow OBJECT-TYPE
	SYNTAX WifiLevel MAX-ACCESS read-write STATUS current DESCRIPTION
	"Signal level from the AP dedicated to data transfer, below
	which a handover to a candidate will be attempted.
	[FW:E2148.AC.1:4.12.0.1]"
	::= { roamingPLHrear 3 }

roamingPLHrearCurrentHigh OBJECT-TYPE
	SYNTAX WifiLevel MAX-ACCESS read-write STATUS current DESCRIPTION
	"Signal level from the AP dedicated to data transfer, above
	which a handover to a candidate will be attempted.
	[FW:E2148.AC.1:4.12.0.1]"
	::= { roamingPLHrear 4 }

-- dual roaming configuration }

-- ====================================
-- serviceStatus (config files state) {
--
ss-webserver OBJECT IDENTIFIER ::= { serviceStatus 1 }
ss-dhcp OBJECT IDENTIFIER ::= { serviceStatus 2 }
ss-ntp OBJECT IDENTIFIER ::= { serviceStatus 3 }
ss-radius OBJECT IDENTIFIER ::= { serviceStatus 4 }
ss-snmp OBJECT IDENTIFIER ::= { serviceStatus 5 }
ss-dns OBJECT IDENTIFIER ::= { serviceStatus 6 }
ss-system OBJECT IDENTIFIER ::= { serviceStatus 7 }
ss-gnss OBJECT IDENTIFIER ::= { serviceStatus 8 }
ss-tcn OBJECT IDENTIFIER ::= { serviceStatus 9 }
ss-async-sysupgrade OBJECT IDENTIFIER ::= { serviceStatus 10 }

-- serviceStatus }

-- SNMP agent variants (to distinguish WLg and WLn through sysObjectID) {
snmpAgentOIDTable OBJECT-TYPE
	SYNTAX SEQUENCE OF SnmpAgentOIDEntry
	MAX-ACCESS not-accessible STATUS current
	DESCRIPTION "List of SNMP agents variants for this entreprise
		    [FW:E2148.AC.1:2.8.0.1]"
	::= { ss-snmp 1 }

snmpAgentOIDEntry OBJECT-TYPE
	SYNTAX SnmpAgentOIDEntry
	MAX-ACCESS not-accessible STATUS current
	DESCRIPTION "Details about the SNMP agent implementation"
	INDEX { snmpAgentOIDIndex }
	::= { snmpAgentOIDTable 1 }

	-- Elements in the IP routes configuration table

	SnmpAgentOIDEntry ::= SEQUENCE {
		snmpAgentOIDIndex INTEGER
		,snmpAgentOIDProductID INTEGER
	}

	snmpAgentOIDIndex OBJECT-TYPE
		SYNTAX INTEGER MAX-ACCESS read-only STATUS current
		DESCRIPTION "Agent variant ID"
		::= { snmpAgentOIDEntry 1 }

	snmpAgentOIDProductID OBJECT-TYPE
		SYNTAX INTEGER MAX-ACCESS read-only STATUS current
		DESCRIPTION "Product ID code currently handled by this agent"
		::= { snmpAgentOIDEntry 2 }

systemReady OBJECT-TYPE
	SYNTAX INTEGER {
		not-ready(1)
		,ready(2)
	} MAX-ACCESS  read-only
    STATUS  current
    DESCRIPTION "This OID returns 2 when the product is fully initialized and
				ready to communicate. It returns 1 instead.
				Please refer to the wireless status in order to check the state
				of the wireless link.
			       [FW:E2148.AC.1:2.8.0.1]"
    ::= { ss-system 1 }

sensors OBJECT IDENTIFIER::= {ss-system 2}
tempSensors OBJECT IDENTIFIER::= {sensors 1}

-- { Temperature sensors
motherBoard0 OBJECT-TYPE
    SYNTAX      Integer32
    MAX-ACCESS  read-only
    STATUS      current
    DESCRIPTION
        "The temperature given by the motherboard sensor 0 in mC. A temperature
		 equals or below -274000mC means that the sensor is not available.
		[FW:E2148.AC.1:2.8.0.1]"
    ::= { tempSensors 1 }

-- }

-- { Gpio input table
gpioInTable OBJECT-TYPE
	SYNTAX SEQUENCE OF GpioInEntry
	MAX-ACCESS not-accessible STATUS current
	DESCRIPTION "Digital input table
		    [FW:E2148.AC.1:3.16.0.1]"
	::= { sensors 2 }

gpioInEntry OBJECT-TYPE
	SYNTAX GpioInEntry
	MAX-ACCESS not-accessible STATUS current
	DESCRIPTION "Digital input table
		    [FW:E2148.AC.1:3.16.0.1]"
	INDEX { gpioInIndex }
	::= { gpioInTable 1 }

	-- Elements in the gpio in table

	GpioInEntry ::=
	    SEQUENCE {
			gpioInIndex INTEGER,
			gpioInState INTEGER
		}

	gpioInIndex OBJECT-TYPE
		SYNTAX INTEGER
		MAX-ACCESS read-only STATUS current
		DESCRIPTION "gpio index"
		::= { gpioInEntry 1 }

	gpioInState OBJECT-TYPE
		SYNTAX INTEGER
		MAX-ACCESS read-only STATUS current
		DESCRIPTION "gpio index"
		::= { gpioInEntry 2 }
-- }
-- { Gpio output table
gpioOutTable OBJECT-TYPE
	SYNTAX SEQUENCE OF GpioOutEntry
	MAX-ACCESS not-accessible STATUS current
	DESCRIPTION "Digital output table
		    [FW:E2148.AC.1:3.16.0.1]"
	::= { sensors 3 }

gpioOutEntry OBJECT-TYPE
	SYNTAX GpioOutEntry
	MAX-ACCESS not-accessible STATUS current
	DESCRIPTION "Digital output table
		    [FW:E2148.AC.1:3.16.0.1]"
	INDEX { gpioOutIndex }
	::= { gpioOutTable 1 }

	-- Elements in the gpio in table

	GpioOutEntry ::=
	    SEQUENCE {
			gpioOutIndex INTEGER,
			gpioOutState INTEGER
		}

	gpioOutIndex OBJECT-TYPE
		SYNTAX INTEGER
		MAX-ACCESS read-only STATUS current
		DESCRIPTION "gpio index"
		::= { gpioOutEntry 1 }

	gpioOutState OBJECT-TYPE
		SYNTAX INTEGER
		MAX-ACCESS read-write STATUS current
		DESCRIPTION "gpio index"
		::= { gpioOutEntry 2 }
-- }
gnss-current-position OBJECT IDENTIFIER::= {ss-gnss 1}

positionValid OBJECT-TYPE
	SYNTAX INTEGER {
			false(1),
			true(2)
			}
	MAX-ACCESS read-only
	STATUS      current
	DESCRIPTION "Indicates if the GPS has managed to determine
		     the position or not.
		     [FW:E2148.AC.1:3.14.0.1]
		    "
	::= { gnss-current-position 1 }

fixdate OBJECT-TYPE
	SYNTAX OCTET STRING
	MAX-ACCESS read-only
	STATUS      current
	DESCRIPTION "UTC date format YYYYMMDD
		     [FW:E2148.AC.1:4.14.0.1]
		    "
	::= { gnss-current-position 2 }

fixtime OBJECT-TYPE
	SYNTAX OCTET STRING
	MAX-ACCESS read-only
	STATUS      current
	DESCRIPTION "UTC time format HHMMSS.mmm
		     [FW:E2148.AC.1:3.14.0.1]
		    "
	::= { gnss-current-position 3 }

latitude OBJECT-TYPE
	 SYNTAX OCTET STRING
	 MAX-ACCESS read-only
	 STATUS      current
	 DESCRIPTION "Value in degrees
	 	      [FW:E2148.AC.1:3.14.0.1]
		     "
	 ::= { gnss-current-position 4 }

longitude OBJECT-TYPE
	  SYNTAX OCTET STRING
	  MAX-ACCESS read-only
	  STATUS      current
	  DESCRIPTION "Value in degrees
	 	      [FW:E2148.AC.1:3.14.0.1]
		      "
	  ::= { gnss-current-position 5 }

altitude OBJECT-TYPE
	 SYNTAX OCTET STRING
	 MAX-ACCESS read-only
	 STATUS      current
	 DESCRIPTION "Value in meters
	 	      [FW:E2148.AC.1:3.14.0.1]
		     "
	 ::= { gnss-current-position 6 }

speedkmh OBJECT-TYPE
	 SYNTAX OCTET STRING
	 MAX-ACCESS read-only
	 STATUS      current
	 DESCRIPTION "speed in km/h
	 	      [FW:E2148.AC.1:3.14.0.1]
		     "
	 ::= { gnss-current-position 7 }

courseDegrees OBJECT-TYPE
	      SYNTAX OCTET STRING
	      MAX-ACCESS read-only
	      STATUS      current
	      DESCRIPTION "Direction angle from North
			   Valid only if speed not null.
			   Return a type string
	 	           [FW:E2148.AC.1:3.14.0.1]
		          "
	      ::= { gnss-current-position 8 }

fixdimension OBJECT-TYPE
	     SYNTAX INTEGER
	     MAX-ACCESS read-only
	     STATUS      current
	     DESCRIPTION "Returns 2 for latitude/longitude only, 3 when
	     		  altitude is available, 0 when fix is invalid.
	 	          [FW:E2148.AC.1:3.14.0.1]
		         "
	     ::= { gnss-current-position 9 }

gnssAllPositions OBJECT-TYPE
	     SYNTAX OCTET STRING
	     MAX-ACCESS read-only
	     STATUS      current
	     DESCRIPTION "Returns all GNSS fix data in a single column-separated string.
	     		  The fields order is as follows: positionValid, fixDimension,
			  fixDate, fixTime, latitude, longitude, altitude, speedkmh,
			  courseDegrees.
	 	          [FW:E2148.AC.1:3.14.0.1]
		         "
	     ::= { gnss-current-position 10 }

-- Table DHCP }%%%%%%

-- async sysupgrade {
firmwareExists OBJECT-TYPE
	SYNTAX INTEGER {
		false(1),
		true(2)
	}
	MAX-ACCESS read-only
	STATUS current
	DESCRIPTION "True if there is a valid firmware uploaded to the product.
				[FW:E2148.AC.1:4.16.0.1]"
	::= { ss-async-sysupgrade 1 }

firmwareInfo OBJECT-TYPE
	SYNTAX OCTET STRING
	MAX-ACCESS read-only
	STATUS current
	DESCRIPTION "Version of all parts in the uploaded firmware and check checksum of uploaded firmware.
				Pattern: [part1 name]:[part1 version];[part2 name]:[part2 version];...;[checksum method]:[checksum value]
				[FW:E2148.AC.1:4.16.0.1]"
	::= { ss-async-sysupgrade 2 }

sysupgradeMissed OBJECT-TYPE
	SYNTAX INTEGER {
		false(1),
		true(2)
	}
	MAX-ACCESS read-only
	STATUS current
	DESCRIPTION "True if there is a missed sysupgrade.
				[FW:E2148.AC.1:4.16.0.1]"
	::= { ss-async-sysupgrade 3 }

-- async sysupgrade }

-- ===========================================
-- serviceConfiguration (config files state) {
--
sc-webserver OBJECT IDENTIFIER ::= { serviceConfiguration 1 }
sc-dhcp OBJECT IDENTIFIER ::= { serviceConfiguration 2 }
sc-ntp OBJECT IDENTIFIER ::= { serviceConfiguration 3 }
sc-radius OBJECT IDENTIFIER ::= { serviceConfiguration 4 }
sc-snmp OBJECT IDENTIFIER ::= { serviceConfiguration 5 }
sc-dns OBJECT IDENTIFIER ::= { serviceConfiguration 6 }
sc-ssh OBJECT IDENTIFIER ::= { serviceConfiguration 7 }
sc-tcn OBJECT IDENTIFIER ::= { serviceConfiguration 8 }
sc-collectd OBJECT IDENTIFIER ::= { serviceConfiguration 9 }
sc-passpoint OBJECT IDENTIFIER ::= { serviceConfiguration 10 }
sc-async-sysupgrade OBJECT IDENTIFIER ::= { serviceConfiguration 11 }
sc-md5sum OBJECT IDENTIFIER ::= { serviceConfiguration 12 }

-- Http(s) server configuration
configHttpServer OBJECT-TYPE
	SYNTAX DisableEnable MAX-ACCESS read-write STATUS current
	DESCRIPTION " Enable / disable the internal Http server.
		     [FW:E2148.AC.1:2.8.0.1]"
    ::= { sc-webserver 1 }

configHttpServerPort OBJECT-TYPE
	SYNTAX INTEGER(1..65535) MAX-ACCESS read-write STATUS current
	DESCRIPTION "Internal Http server TCP port. If the http server is disabled,
		     this OID returns 0
		    [FW:E2148.AC.1:2.8.0.1]"
    ::= { sc-webserver 2 }

configHttpsServer OBJECT-TYPE
	SYNTAX DisableEnable MAX-ACCESS read-write STATUS current
	DESCRIPTION "Enable / disable the internal Https server.
		    [FW:E2148.AC.1:2.8.0.1]"
    ::= { sc-webserver 3 }

configHttpsPort OBJECT-TYPE
	SYNTAX INTEGER(1..65535) MAX-ACCESS read-write STATUS current
	DESCRIPTION "Internal Https server TCP port. If the https server is disabled,
		     this OID returns 0
		    [FW:E2148.AC.1:2.8.0.1]"
    ::= { sc-webserver 4 }

configHttpsCertificate OBJECT-TYPE
	SYNTAX OCTET STRING MAX-ACCESS read-write STATUS current
	DESCRIPTION "Internal Https server certificate.
		A GET for this OID returns a string whose first
		byte is '1' if the key was uploaded, else '0'
		[FW:E2148.AC.1:2.8.0.1]"
    ::= { sc-webserver 5 }

-- Tables - DHCP servers {
configDhcpTable OBJECT-TYPE
	SYNTAX SEQUENCE OF ConfigDhcpEntry
	MAX-ACCESS not-accessible STATUS current
	DESCRIPTION "List of DHCP servers per subnet
		    [FW:E2148.AC.1:2.8.0.1]"
	::= { sc-dhcp 1 }

configDhcpEntry OBJECT-TYPE
	SYNTAX ConfigDhcpEntry
	MAX-ACCESS not-accessible STATUS current
	DESCRIPTION "Details about a configured DHCP server
		    [FW:E2148.AC.1:2.8.0.1]"
	INDEX { configDhcpSubnet }
	::= { configDhcpTable 1 }

	-- Elements in the IP routes configuration table

	ConfigDhcpEntry ::= SEQUENCE {
		configDhcpSubnet NetifName
		,configDhcpRowStatus RowStatus
		,configDhcpEnable INTEGER
		,configDhcpPoolStart INTEGER
		,configDhcpPoolCount INTEGER
		,configDhcpLeaseDuration INTEGER
	}

	configDhcpSubnet OBJECT-TYPE
		SYNTAX NetifName MAX-ACCESS read-write STATUS current
		DESCRIPTION "Interface on which this DHCP server instance is run"
		::= { configDhcpEntry 1 }

	configDhcpRowStatus OBJECT-TYPE
		SYNTAX RowStatus MAX-ACCESS read-create STATUS current
		DESCRIPTION "row addition/deletion support
		[net]
		[MAX-ACCESS:read-only]"
		::= { configDhcpEntry 2 }

	configDhcpEnable OBJECT-TYPE
		SYNTAX DisableEnable MAX-ACCESS read-write STATUS current
		DESCRIPTION "Enable DHCP server instance"
		::= { configDhcpEntry 3 }

	configDhcpPoolStart OBJECT-TYPE
		SYNTAX INTEGER MAX-ACCESS read-write STATUS current
		DESCRIPTION "First IP address in the pool"
		::= { configDhcpEntry 4 }

	configDhcpPoolCount OBJECT-TYPE
		SYNTAX INTEGER MAX-ACCESS read-write STATUS current
		DESCRIPTION "Number of IP addresses in the pool"
		::= { configDhcpEntry 5 }

	configDhcpLeaseDuration OBJECT-TYPE
		SYNTAX INTEGER MAX-ACCESS read-write STATUS current
		DESCRIPTION "Lease time (seconds)"
		::= { configDhcpEntry 6 }
-- Table DHCP }

-- NTP {
configNtp OBJECT-TYPE
	SYNTAX INTEGER
	MAX-ACCESS not-accessible STATUS current
	DESCRIPTION "Not implemented yet"
	::= { sc-ntp 1 }
-- NTP }

-- DNS configuration {
configRelay OBJECT IDENTIFIER ::= { sc-dns 1 }
	-- DNS Relay configuration {
	configDnsRebindProtection OBJECT-TYPE
		SYNTAX DisableEnable MAX-ACCESS read-write STATUS current
		DESCRIPTION " Enable / disable DNS rebind attack protection.
			[FW:E2148.AC.1:2.8.0.1]"
	    ::= { configRelay 1 }

	configDnsRebindLocalhost OBJECT-TYPE
		SYNTAX DisableEnable MAX-ACCESS read-write STATUS current
		DESCRIPTION " Allow / Disallow DNS response with IP address in 127.0.0.0/8 range.
			[FW:E2148.AC.1:2.8.0.1]"
	    ::= { configRelay 2 }
	-- DNS Relay configuration }
-- DNS configuration }

-- SSH configuration {

configSshEnable OBJECT-TYPE
	SYNTAX DisableEnable MAX-ACCESS read-write STATUS current
	DESCRIPTION "Enable ssh
		    [FW:E2148.AC.1:2.8.0.1]"
    ::= { sc-ssh 1 }

configSshEnablePwd OBJECT-TYPE
	SYNTAX DisableEnable MAX-ACCESS read-write STATUS current
	DESCRIPTION "Enable ssh user/password login
		    [FW:E2148.AC.1:4.16.0.1]"
    ::= { sc-ssh 2 }

-- SSH configuration }

-- MD5SUM {

configMD5SUMstatus OBJECT-TYPE
	SYNTAX INTEGER MAX-ACCESS read-write STATUS current
	DESCRIPTION "Set any value to re-calculate md5 sums of filesystem.
			Do a GET to get number of failed files.
		    [FW:E2148.AC.1:4.16.0.1]"
    ::= { sc-md5sum 1 }

configMD5SUMfiles OBJECT-TYPE
	SYNTAX DisplayString MAX-ACCESS read-only STATUS current
	DESCRIPTION "Return the failed files list
		    [FW:E2148.AC.1:4.16.0.1]"
    ::= { sc-md5sum 2 }

-- MD5SUM }

-- Table - Acksys Telemetry {

configCollectdEnable OBJECT-TYPE
	SYNTAX DisableEnable MAX-ACCESS read-write STATUS current
	DESCRIPTION "Collectd service enable
	[FW:E2148.AC.1:4.10.0.1]"
	::= { sc-collectd 1 }

configCollectdSamplingInterval OBJECT-TYPE
	SYNTAX INTEGER(1..255) MAX-ACCESS read-write STATUS current
	DESCRIPTION "Collectd sampling interval in seconds
	[FW:E2148.AC.1:4.10.0.1]"
	::= { sc-collectd 2 }

plugin-GPS OBJECT IDENTIFIER ::= { sc-collectd 3 }

configCollectdGPSEnable OBJECT-TYPE
	SYNTAX DisableEnable MAX-ACCESS read-write STATUS current
	DESCRIPTION "Collectd plugin GPS enable
	[FW:E2148.AC.1:4.10.0.1]"
	::= { plugin-GPS 1 }

configCollectdGPSServerAddr OBJECT-TYPE
	SYNTAX IpAddress MAX-ACCESS read-write STATUS current
	DESCRIPTION "Collectd plugin GPS server's IP address
	[FW:E2148.AC.1:4.10.0.1]"
	::= { plugin-GPS 2 }

configCollectdGPSServerPort OBJECT-TYPE
	SYNTAX INTEGER(1..65535) MAX-ACCESS read-write STATUS current
	DESCRIPTION "Collectd plugin GPS server's port
	[FW:E2148.AC.1:4.10.0.1]"
	::= { plugin-GPS 3 }

configCollectdGPSConnTimeout OBJECT-TYPE
	SYNTAX INTEGER(1..255) MAX-ACCESS read-write STATUS current
	DESCRIPTION "Collectd plugin GPS connection timeout in seconds
	[FW:E2148.AC.1:4.10.0.1]"
	::= { plugin-GPS 4 }

configCollectdGPSReqInterval OBJECT-TYPE
	SYNTAX INTEGER(1..255) MAX-ACCESS read-write STATUS current
	DESCRIPTION "Collectd plugin GPS request interval in seconds
	[FW:E2148.AC.1:4.10.0.1]"
	::= { plugin-GPS 5 }

plugin-AcksysScanResult OBJECT IDENTIFIER ::= { sc-collectd 4 }

configCollectdWirelessScanResult OBJECT-TYPE
	SYNTAX DisableEnable MAX-ACCESS read-write STATUS current
	DESCRIPTION "Enable wireless scan result collection
	[FW:E2148.AC.1:4.10.0.1]"
	::= { plugin-AcksysScanResult 1 }

plugin-iwinfo OBJECT IDENTIFIER ::= { sc-collectd 5 }

configCollectdIwinfo OBJECT-TYPE
	SYNTAX DisableEnable MAX-ACCESS read-write STATUS current
	DESCRIPTION "Enable wireless info collection
	[FW:E2148.AC.1:4.10.0.1]"
	::= { plugin-iwinfo 1 }

plugin-AcksysTelemetry OBJECT IDENTIFIER ::= { sc-collectd 6 }

configAcksysTelemetryEnable OBJECT-TYPE
	SYNTAX DisableEnable MAX-ACCESS read-write STATUS current
	DESCRIPTION "Enable Acksys telemetry plugin
	[FW:E2148.AC.1:4.10.0.1]"
	::= { plugin-AcksysTelemetry 1 }

configAcksysTelemetryServerPort OBJECT-TYPE
	SYNTAX INTEGER(1..65535) MAX-ACCESS read-write STATUS current
	DESCRIPTION "Acksys telemetry plugin server's port
	[FW:E2148.AC.1:4.10.0.1]"
	::= { plugin-AcksysTelemetry 2 }

configAcksysTelemetryOutputInterval OBJECT-TYPE
	SYNTAX INTEGER(1..255) MAX-ACCESS read-write STATUS current
	DESCRIPTION "Interval in seconds of Acksys telemetry data transmission
	[FW:E2148.AC.1:4.10.0.1]"
	::= { plugin-AcksysTelemetry 3 }

configAcksysTelemetryMaxBufferSize OBJECT-TYPE
	SYNTAX INTEGER(1..65535) MAX-ACCESS read-write STATUS current
	DESCRIPTION "Size of buffer that acksys telemetry used internally
	[FW:E2148.AC.1:4.10.0.1]"
	::= { plugin-AcksysTelemetry 4 }

-- Table - Acksys Telemetry }

-- Service Passpoint {
-- Table Passpoint config {

configPasspointConfigTable OBJECT-TYPE
	SYNTAX SEQUENCE OF ConfigPasspointConfigEntry
	MAX-ACCESS not-accessible
	STATUS current
	DESCRIPTION	"List of Passpoint configurations
				[FW:E2148.AC.1:X.XX.X.X]"
	::= { sc-passpoint 1 }

configPasspointConfigEntry OBJECT-TYPE
	SYNTAX ConfigPasspointConfigEntry
	MAX-ACCESS not-accessible
	STATUS current
	DESCRIPTION	"Entry of Passpoint configuration
				[FW:E2148.AC.1:X.XX.X.X]"
	INDEX { configPasspointConfigName }
	::= { configPasspointConfigTable 1 }

ConfigPasspointConfigEntry ::=
	SEQUENCE {
		configPasspointConfigName OCTET STRING
		,configPasspointConfigRowStatus RowStatus
		,configPasspointConfigAnqpAccessNetworkType INTEGER
		,configPasspointConfigAnqpInternet DisableEnable
		,configPasspointConfigAnqpAsra DisableEnable
		,configPasspointConfigAnqpEsr DisableEnable
		,configPasspointConfigAnqpUesa DisableEnable
		,configPasspointConfigAnqpHessid OCTET STRING
		,configPasspointConfigAnqpGasAddress3 INTEGER
		,configPasspointConfigAnqpVenueProfile OCTET STRING
		,configPasspointConfigAnqpRoamingConsortiumProfile OCTET STRING
		,configPasspointConfigAnqpNetworkAuthTypeProfile OCTET STRING
		,configPasspointConfigAnqpIpAddrTypeAvailProfile OCTET STRING
		,configPasspointConfigAnqpDomainNameProfile OCTET STRING
		,configPasspointConfigAnqp3gppCellNetProfile OCTET STRING
		,configPasspointConfigAnqpNaiRealmProfile OCTET STRING
		,configPasspointConfigAnqpOverrideElementProfile OCTET STRING
		,configPasspointConfigHS20DisableDgaf DisableEnable
		,configPasspointConfigHS20DomainId INTEGER
		,configPasspointConfigHS20DeauthReqTimeout INTEGER
		,configPasspointConfigHS20OsuSsid OCTET STRING
		,configPasspointConfigHS20OperFriendlyNameProfile OCTET STRING
		,configPasspointConfigHS20ConnCapProfile OCTET STRING
		,configPasspointConfigHS20WanMetricsProfile OCTET STRING
		,configPasspointConfigHS20OperClassProfile OCTET STRING
		,configPasspointConfigHS20OsuProviderProfile OCTET STRING
	}

	configPasspointConfigName OBJECT-TYPE
		SYNTAX OCTET STRING MAX-ACCESS read-write STATUS current
		DESCRIPTION "configPasspointConfigName"
		::= { configPasspointConfigEntry 1 }

	configPasspointConfigRowStatus OBJECT-TYPE
		SYNTAX RowStatus MAX-ACCESS read-create STATUS current
		DESCRIPTION "row addition/deletion support"
		::= { configPasspointConfigEntry 2 }

	configPasspointConfigAnqpAccessNetworkType OBJECT-TYPE
		SYNTAX INTEGER MAX-ACCESS read-write STATUS current
		DESCRIPTION "configPasspointConfigAnqpAccessNetworkType"
		::= { configPasspointConfigEntry 3 }

	configPasspointConfigAnqpInternet OBJECT-TYPE
		SYNTAX DisableEnable MAX-ACCESS read-write STATUS current
		DESCRIPTION "configPasspointConfigAnqpInternet"
		::= { configPasspointConfigEntry 4 }

	configPasspointConfigAnqpAsra OBJECT-TYPE
		SYNTAX DisableEnable MAX-ACCESS read-write STATUS current
		DESCRIPTION "configPasspointConfigAnqpAsra"
		::= { configPasspointConfigEntry 5 }

	configPasspointConfigAnqpEsr OBJECT-TYPE
		SYNTAX DisableEnable MAX-ACCESS read-write STATUS current
		DESCRIPTION "configPasspointConfigAnqpEsr"
		::= { configPasspointConfigEntry 6 }

	configPasspointConfigAnqpUesa OBJECT-TYPE
		SYNTAX DisableEnable MAX-ACCESS read-write STATUS current
		DESCRIPTION "configPasspointConfigAnqpUesa"
		::= { configPasspointConfigEntry 7 }

	configPasspointConfigAnqpHessid OBJECT-TYPE
		SYNTAX OCTET STRING MAX-ACCESS read-write STATUS current
		DESCRIPTION "configPasspointConfigAnqpHessid"
		::= { configPasspointConfigEntry 8 }

	configPasspointConfigAnqpGasAddress3 OBJECT-TYPE
		SYNTAX INTEGER { p2p(0), ieee80211-std(1), non-compliant(2)}
		MAX-ACCESS read-write STATUS current
		DESCRIPTION "configPasspointConfigAnqpGasAddress3"
		::= { configPasspointConfigEntry 9 }

	configPasspointConfigAnqpVenueProfile OBJECT-TYPE
		SYNTAX OCTET STRING MAX-ACCESS read-write STATUS current
		DESCRIPTION "configPasspointConfigAnqpVenueProfile"
		::= { configPasspointConfigEntry 10 }

	configPasspointConfigAnqpRoamingConsortiumProfile OBJECT-TYPE
		SYNTAX OCTET STRING MAX-ACCESS read-write STATUS current
		DESCRIPTION "configPasspointConfigAnqpRoamingConsortiumProfile"
		::= { configPasspointConfigEntry 11 }

	configPasspointConfigAnqpNetworkAuthTypeProfile OBJECT-TYPE
		SYNTAX OCTET STRING MAX-ACCESS read-write STATUS current
		DESCRIPTION "configPasspointConfigAnqpNetworkAuthTypeProfile"
		::= { configPasspointConfigEntry 12 }

	configPasspointConfigAnqpIpAddrTypeAvailProfile OBJECT-TYPE
		SYNTAX OCTET STRING MAX-ACCESS read-write STATUS current
		DESCRIPTION "configPasspointConfigAnqpIpAddrTypeAvailProfile"
		::= { configPasspointConfigEntry 13 }

	configPasspointConfigAnqpDomainNameProfile OBJECT-TYPE
		SYNTAX OCTET STRING MAX-ACCESS read-write STATUS current
		DESCRIPTION "configPasspointConfigAnqpDomainNameProfile"
		::= { configPasspointConfigEntry 14 }

	configPasspointConfigAnqp3gppCellNetProfile OBJECT-TYPE
		SYNTAX OCTET STRING MAX-ACCESS read-write STATUS current
		DESCRIPTION "configPasspointConfigAnqp3gppCellNetProfile"
		::= { configPasspointConfigEntry 15 }

	configPasspointConfigAnqpNaiRealmProfile OBJECT-TYPE
		SYNTAX OCTET STRING MAX-ACCESS read-write STATUS current
		DESCRIPTION "configPasspointConfigAnqpNaiRealmProfile"
		::= { configPasspointConfigEntry 16 }

	configPasspointConfigAnqpOverrideElementProfile OBJECT-TYPE
		SYNTAX OCTET STRING MAX-ACCESS read-write STATUS current
		DESCRIPTION "configPasspointConfigAnqpOverrideElementProfile"
		::= { configPasspointConfigEntry 17 }

	configPasspointConfigHS20DisableDgaf OBJECT-TYPE
		SYNTAX DisableEnable MAX-ACCESS read-write STATUS current
		DESCRIPTION "configPasspointConfigHS20DisableDgaf"
		::= { configPasspointConfigEntry 18 }

	configPasspointConfigHS20DomainId OBJECT-TYPE
		SYNTAX INTEGER MAX-ACCESS read-write STATUS current
		DESCRIPTION "configPasspointConfigHS20DomainId"
		::= { configPasspointConfigEntry 19 }

	configPasspointConfigHS20DeauthReqTimeout OBJECT-TYPE
		SYNTAX INTEGER MAX-ACCESS read-write STATUS current
		DESCRIPTION "configPasspointConfigHS20DeauthReqTimeout"
		::= { configPasspointConfigEntry 20 }

	configPasspointConfigHS20OsuSsid OBJECT-TYPE
		SYNTAX OCTET STRING MAX-ACCESS read-write STATUS current
		DESCRIPTION "configPasspointConfigHS20OsuSsid"
		::= { configPasspointConfigEntry 21 }

	configPasspointConfigHS20OperFriendlyNameProfile OBJECT-TYPE
		SYNTAX OCTET STRING MAX-ACCESS read-write STATUS current
		DESCRIPTION "configPasspointConfigHS20OperFriendlyNameProfile"
		::= { configPasspointConfigEntry 22 }

	configPasspointConfigHS20ConnCapProfile OBJECT-TYPE
		SYNTAX OCTET STRING MAX-ACCESS read-write STATUS current
		DESCRIPTION "configPasspointConfigHS20ConnCapProfile"
		::= { configPasspointConfigEntry 23 }

	configPasspointConfigHS20WanMetricsProfile OBJECT-TYPE
		SYNTAX OCTET STRING MAX-ACCESS read-write STATUS current
		DESCRIPTION "configPasspointConfigHS20WanMetricsProfile"
		::= { configPasspointConfigEntry 24 }

	configPasspointConfigHS20OperClassProfile OBJECT-TYPE
		SYNTAX OCTET STRING MAX-ACCESS read-write STATUS current
		DESCRIPTION "configPasspointConfigHS20OperClassProfile"
		::= { configPasspointConfigEntry 25 }

	configPasspointConfigHS20OsuProviderProfile OBJECT-TYPE
		SYNTAX OCTET STRING MAX-ACCESS read-write STATUS current
		DESCRIPTION "configPasspointConfigHS20OsuProviderProfile"
		::= { configPasspointConfigEntry 26 }

-- Table Passpoint config }

configAnqpProfileVenueTable OBJECT-TYPE
	SYNTAX SEQUENCE OF ConfigAnqpProfileVenueEntry
	MAX-ACCESS not-accessible
	STATUS current
	DESCRIPTION	"List of configAnqpProfileVenueTable
				[FW:E2148.AC.1:X.XX.X.X]"
	::= { sc-passpoint 2 }

configAnqpProfileVenueEntry OBJECT-TYPE
	SYNTAX ConfigAnqpProfileVenueEntry
	MAX-ACCESS not-accessible
	STATUS current
	DESCRIPTION "List of configAnqpProfileVenue
				[FW:E2148.AC.1:X.XX.X.X]"
	INDEX { configProfileVenueName }
	::={ configAnqpProfileVenueTable 1 }

ConfigAnqpProfileVenueEntry ::=
	SEQUENCE {
		configProfileVenueName OCTET STRING
		,configProfileVenueRowStatus RowStatus
		,configProfileVenueDesc OCTET STRING
		,configVenueGroup INTEGER
		,configVenueType INTEGER
		,configVenueNameList OCTET STRING
	}

	configProfileVenueName OBJECT-TYPE
		SYNTAX OCTET STRING MAX-ACCESS read-only STATUS current
		DESCRIPTION "profile name, which will be referred in passpoint config."
		::= { configAnqpProfileVenueEntry 1 }

	configProfileVenueRowStatus OBJECT-TYPE
		SYNTAX RowStatus MAX-ACCESS read-create STATUS current
		DESCRIPTION "row addition/deletion support"
		::= { configAnqpProfileVenueEntry 2 }

	configProfileVenueDesc OBJECT-TYPE
		SYNTAX OCTET STRING MAX-ACCESS read-write STATUS current
		DESCRIPTION "profile description."
		::= { configAnqpProfileVenueEntry 3 }

	configVenueGroup OBJECT-TYPE
		SYNTAX INTEGER MAX-ACCESS read-write STATUS current
		DESCRIPTION "Venue groupe"
		::= { configAnqpProfileVenueEntry 4 }

	configVenueType OBJECT-TYPE
		SYNTAX INTEGER MAX-ACCESS read-write STATUS current
		DESCRIPTION "Venue groupe"
		::= { configAnqpProfileVenueEntry 5 }

	configVenueNameList OBJECT-TYPE
		SYNTAX OCTET STRING MAX-ACCESS read-write STATUS current
		DESCRIPTION "Venue name. Format: [country 1 code]:[name 1 string],[country 2 code]:[name 2 string]..."
		::= { configAnqpProfileVenueEntry 6 }

configAnqpProfileRoamingConsortiumTable OBJECT-TYPE
	SYNTAX SEQUENCE OF ConfigAnqpProfileRoamingConsortiumEntry
	MAX-ACCESS not-accessible
	STATUS current
	DESCRIPTION	"List of configAnqpProfileRoamingConsortiumTable
				[FW:E2148.AC.1:X.XX.X.X]"
	::= { sc-passpoint 3 }

configAnqpProfileRoamingConsortiumEntry OBJECT-TYPE
	SYNTAX ConfigAnqpProfileRoamingConsortiumEntry
	MAX-ACCESS not-accessible
	STATUS current
	DESCRIPTION "List of configAnqpProfileRoamingConsortium
				[FW:E2148.AC.1:X.XX.X.X]"
	INDEX { configProfileRoamingConsortiumName }
	::={ configAnqpProfileRoamingConsortiumTable 1 }

ConfigAnqpProfileRoamingConsortiumEntry ::=
	SEQUENCE {
		configProfileRoamingConsortiumName OCTET STRING
		,configProfileRoamingConsortiumRowStatus RowStatus
		,configProfileRoamingConsortiumDesc OCTET STRING
		,configRoamingConsortiumList OCTET STRING
	}

	configProfileRoamingConsortiumName OBJECT-TYPE
		SYNTAX OCTET STRING MAX-ACCESS read-only STATUS current
		DESCRIPTION "profile name, which will be referred in passpoint config."
		::= { configAnqpProfileRoamingConsortiumEntry 1 }

	configProfileRoamingConsortiumRowStatus OBJECT-TYPE
		SYNTAX RowStatus MAX-ACCESS read-create STATUS current
		DESCRIPTION "row addition/deletion support"
		::= { configAnqpProfileRoamingConsortiumEntry 2 }

	configProfileRoamingConsortiumDesc OBJECT-TYPE
		SYNTAX OCTET STRING MAX-ACCESS read-write STATUS current
		DESCRIPTION "profile description."
		::= { configAnqpProfileRoamingConsortiumEntry 3 }

	configRoamingConsortiumList OBJECT-TYPE
		SYNTAX OCTET STRING MAX-ACCESS read-write STATUS current
		DESCRIPTION "List of roaming consortium."
		::= { configAnqpProfileRoamingConsortiumEntry 4 }

configAnqpProfileNetworkAuthTypeTable OBJECT-TYPE
	SYNTAX SEQUENCE OF ConfigAnqpProfileNetworkAuthTypeEntry
	MAX-ACCESS not-accessible
	STATUS current
	DESCRIPTION	"List of configAnqpProfileNetworkAuthTypeTable
				[FW:E2148.AC.1:X.XX.X.X]"
	::= { sc-passpoint 4 }

configAnqpProfileNetworkAuthTypeEntry OBJECT-TYPE
	SYNTAX ConfigAnqpProfileNetworkAuthTypeEntry
	MAX-ACCESS not-accessible
	STATUS current
	DESCRIPTION "List of configAnqpProfileNetworkAuthType
				[FW:E2148.AC.1:X.XX.X.X]"
	INDEX { configProfileNetworkAuthTypeName }
	::={ configAnqpProfileNetworkAuthTypeTable 1 }

ConfigAnqpProfileNetworkAuthTypeEntry ::=
	SEQUENCE {
		configProfileNetworkAuthTypeName OCTET STRING
		,configProfileNetworkAuthTypeRowStatus RowStatus
		,configProfileNetworkAuthTypeDesc OCTET STRING
		,configNetworkAuthType OCTET STRING
	}

	configProfileNetworkAuthTypeName OBJECT-TYPE
		SYNTAX OCTET STRING MAX-ACCESS read-only STATUS current
		DESCRIPTION "profile name, which will be referred in passpoint config."
		::= { configAnqpProfileNetworkAuthTypeEntry 1 }

	configProfileNetworkAuthTypeRowStatus OBJECT-TYPE
		SYNTAX RowStatus MAX-ACCESS read-create STATUS current
		DESCRIPTION "row addition/deletion support"
		::= { configAnqpProfileNetworkAuthTypeEntry 2 }

	configProfileNetworkAuthTypeDesc OBJECT-TYPE
		SYNTAX OCTET STRING MAX-ACCESS read-write STATUS current
		DESCRIPTION "profile description."
		::= { configAnqpProfileNetworkAuthTypeEntry 3 }

	configNetworkAuthType OBJECT-TYPE
		SYNTAX OCTET STRING MAX-ACCESS read-write STATUS current
		DESCRIPTION "Network auth type"
		::= { configAnqpProfileNetworkAuthTypeEntry 4 }

configAnqpProfileIpAddrTypeAvailTable OBJECT-TYPE
	SYNTAX SEQUENCE OF ConfigAnqpProfileIpAddrTypeAvailEntry
	MAX-ACCESS not-accessible
	STATUS current
	DESCRIPTION	"List of configAnqpProfileIpAddrTypeAvailTable
				[FW:E2148.AC.1:X.XX.X.X]"
	::= { sc-passpoint 5 }

configAnqpProfileIpAddrTypeAvailEntry OBJECT-TYPE
	SYNTAX ConfigAnqpProfileIpAddrTypeAvailEntry
	MAX-ACCESS not-accessible
	STATUS current
	DESCRIPTION "List of configAnqpProfileIpAddrTypeAvail
				[FW:E2148.AC.1:X.XX.X.X]"
	INDEX { configProfileIpAddrTypeAvailName }
	::={ configAnqpProfileIpAddrTypeAvailTable 1 }

ConfigAnqpProfileIpAddrTypeAvailEntry ::=
	SEQUENCE {
		configProfileIpAddrTypeAvailName OCTET STRING
		,configProfileIpAddrTypeAvailRowStatus RowStatus
		,configProfileIpAddrTypeAvailDesc OCTET STRING
		,configIpv4Type INTEGER
		,configIpv6Type INTEGER
	}

	configProfileIpAddrTypeAvailName OBJECT-TYPE
		SYNTAX OCTET STRING MAX-ACCESS read-only STATUS current
		DESCRIPTION "profile name, which will be referred in passpoint config."
		::= { configAnqpProfileIpAddrTypeAvailEntry 1 }

	configProfileIpAddrTypeAvailRowStatus OBJECT-TYPE
		SYNTAX RowStatus MAX-ACCESS read-create STATUS current
		DESCRIPTION "row addition/deletion support"
		::= { configAnqpProfileIpAddrTypeAvailEntry 2 }

	configProfileIpAddrTypeAvailDesc OBJECT-TYPE
		SYNTAX OCTET STRING MAX-ACCESS read-write STATUS current
		DESCRIPTION "profile description."
		::= { configAnqpProfileIpAddrTypeAvailEntry 3 }

	configIpv4Type OBJECT-TYPE
		SYNTAX INTEGER MAX-ACCESS read-write STATUS current
		DESCRIPTION "IPv4 address availability."
		::= { configAnqpProfileIpAddrTypeAvailEntry 4 }

	configIpv6Type OBJECT-TYPE
		SYNTAX INTEGER MAX-ACCESS read-write STATUS current
		DESCRIPTION "IPv6 address availability."
		::= { configAnqpProfileIpAddrTypeAvailEntry 5 }

configAnqpProfileDomainNameTable OBJECT-TYPE
	SYNTAX SEQUENCE OF ConfigAnqpProfileDomainNameEntry
	MAX-ACCESS not-accessible
	STATUS current
	DESCRIPTION	"List of configAnqpProfileDomainNameTable
				[FW:E2148.AC.1:X.XX.X.X]"
	::= { sc-passpoint 6 }

configAnqpProfileDomainNameEntry OBJECT-TYPE
	SYNTAX ConfigAnqpProfileDomainNameEntry
	MAX-ACCESS not-accessible
	STATUS current
	DESCRIPTION "List of configAnqpProfileDomainName
				[FW:E2148.AC.1:X.XX.X.X]"
	INDEX { configProfileDomainNameName }
	::={ configAnqpProfileDomainNameTable 1 }

ConfigAnqpProfileDomainNameEntry ::=
	SEQUENCE {
		configProfileDomainNameName OCTET STRING
		,configProfileDomainNameRowStatus RowStatus
		,configProfileDomainNameDesc OCTET STRING
		,configDomainNameList OCTET STRING
	}

	configProfileDomainNameName OBJECT-TYPE
		SYNTAX OCTET STRING MAX-ACCESS read-only STATUS current
		DESCRIPTION "profile name, which will be referred in passpoint config."
		::= { configAnqpProfileDomainNameEntry 1 }

	configProfileDomainNameRowStatus OBJECT-TYPE
		SYNTAX RowStatus MAX-ACCESS read-create STATUS current
		DESCRIPTION "row addition/deletion support"
		::= { configAnqpProfileDomainNameEntry 2 }

	configProfileDomainNameDesc OBJECT-TYPE
		SYNTAX OCTET STRING MAX-ACCESS read-write STATUS current
		DESCRIPTION "profile description."
		::= { configAnqpProfileDomainNameEntry 3 }

	configDomainNameList OBJECT-TYPE
		SYNTAX OCTET STRING MAX-ACCESS read-write STATUS current
		DESCRIPTION "Domain name list."
		::= { configAnqpProfileDomainNameEntry 4 }

configAnqpProfile3gppCellNetTable OBJECT-TYPE
	SYNTAX SEQUENCE OF ConfigAnqpProfile3gppCellNetEntry
	MAX-ACCESS not-accessible
	STATUS current
	DESCRIPTION	"List of configAnqpProfile3gppCellNetTable
				[FW:E2148.AC.1:X.XX.X.X]"
	::= { sc-passpoint 7 }

configAnqpProfile3gppCellNetEntry OBJECT-TYPE
	SYNTAX ConfigAnqpProfile3gppCellNetEntry
	MAX-ACCESS not-accessible
	STATUS current
	DESCRIPTION "List of configAnqpProfile3gppCellNet
				[FW:E2148.AC.1:X.XX.X.X]"
	INDEX { configProfile3gppCellNetName }
	::={ configAnqpProfile3gppCellNetTable 1 }

ConfigAnqpProfile3gppCellNetEntry ::=
	SEQUENCE {
		configProfile3gppCellNetName OCTET STRING
		,configProfile3gppCellNetRowStatus RowStatus
		,configProfile3gppCellNetDesc OCTET STRING
		,config3gppCellNetList OCTET STRING
	}

	configProfile3gppCellNetName OBJECT-TYPE
		SYNTAX OCTET STRING MAX-ACCESS read-only STATUS current
		DESCRIPTION "profile name, which will be referred in passpoint config."
		::= { configAnqpProfile3gppCellNetEntry 1 }

	configProfile3gppCellNetRowStatus OBJECT-TYPE
		SYNTAX RowStatus MAX-ACCESS read-create STATUS current
		DESCRIPTION "row addition/deletion support"
		::= { configAnqpProfile3gppCellNetEntry 2 }

	configProfile3gppCellNetDesc OBJECT-TYPE
		SYNTAX OCTET STRING MAX-ACCESS read-write STATUS current
		DESCRIPTION "profile description."
		::= { configAnqpProfile3gppCellNetEntry 3 }

	config3gppCellNetList OBJECT-TYPE
		SYNTAX OCTET STRING MAX-ACCESS read-write STATUS current
		DESCRIPTION "3GPP Cell Net list, MCC1:MNC1;MCC2:MNC2..."
		::= { configAnqpProfile3gppCellNetEntry 4 }

configAnqpProfileNaiRealmTable OBJECT-TYPE
	SYNTAX SEQUENCE OF ConfigAnqpProfileNaiRealmEntry
	MAX-ACCESS not-accessible
	STATUS current
	DESCRIPTION	"List of configAnqpProfileNaiRealmTable
				[FW:E2148.AC.1:X.XX.X.X]"
	::= { sc-passpoint 8 }

configAnqpProfileNaiRealmEntry OBJECT-TYPE
	SYNTAX ConfigAnqpProfileNaiRealmEntry
	MAX-ACCESS not-accessible
	STATUS current
	DESCRIPTION "List of configAnqpProfileNaiRealm
				[FW:E2148.AC.1:X.XX.X.X]"
	INDEX { configProfileNaiRealmName }
	::={ configAnqpProfileNaiRealmTable 1 }

ConfigAnqpProfileNaiRealmEntry ::=
	SEQUENCE {
		configProfileNaiRealmName OCTET STRING
		,configProfileNaiRealmRowStatus RowStatus
		,configProfileNaiRealmDesc OCTET STRING
		,configNaiRealmEncode DisableEnable
		,configNaiRealmRealmList OCTET STRING
		,configNaiRealmEap OCTET STRING
	}

	configProfileNaiRealmName OBJECT-TYPE
		SYNTAX OCTET STRING MAX-ACCESS read-only STATUS current
		DESCRIPTION "profile name, which will be referred in passpoint config."
		::= { configAnqpProfileNaiRealmEntry 1 }

	configProfileNaiRealmRowStatus OBJECT-TYPE
		SYNTAX RowStatus MAX-ACCESS read-create STATUS current
		DESCRIPTION "row addition/deletion support"
		::= { configAnqpProfileNaiRealmEntry 2 }

	configProfileNaiRealmDesc OBJECT-TYPE
		SYNTAX OCTET STRING MAX-ACCESS read-write STATUS current
		DESCRIPTION "profile description."
		::= { configAnqpProfileNaiRealmEntry 3 }

	configNaiRealmEncode OBJECT-TYPE
		SYNTAX DisableEnable MAX-ACCESS read-write STATUS current
		DESCRIPTION "NAI Realm Encode"
		::= { configAnqpProfileNaiRealmEntry 4 }

	configNaiRealmRealmList OBJECT-TYPE
		SYNTAX OCTET STRING MAX-ACCESS read-write STATUS current
		DESCRIPTION "NAI Realm list"
		::= { configAnqpProfileNaiRealmEntry 5 }

	configNaiRealmEap OBJECT-TYPE
		SYNTAX OCTET STRING MAX-ACCESS read-write STATUS current
		DESCRIPTION "NAI Real EAP"
		::= { configAnqpProfileNaiRealmEntry 6 }

configAnqpProfileOverrideElementTable OBJECT-TYPE
	SYNTAX SEQUENCE OF ConfigAnqpProfileOverrideElementEntry
	MAX-ACCESS not-accessible
	STATUS current
	DESCRIPTION	"List of configAnqpProfileOverrideElementTable
				[FW:E2148.AC.1:X.XX.X.X]"
	::= { sc-passpoint 9 }

configAnqpProfileOverrideElementEntry OBJECT-TYPE
	SYNTAX ConfigAnqpProfileOverrideElementEntry
	MAX-ACCESS not-accessible
	STATUS current
	DESCRIPTION "List of configAnqpProfileOverrideElement
				[FW:E2148.AC.1:X.XX.X.X]"
	INDEX { configProfileOverrideElementName }
	::={ configAnqpProfileOverrideElementTable 1 }

ConfigAnqpProfileOverrideElementEntry ::=
	SEQUENCE {
		configProfileOverrideElementName OCTET STRING
		,configProfileOverrideElementRowStatus RowStatus
		,configProfileOverrideElementDesc OCTET STRING
		,configAnqpOverrideList OCTET STRING
	}

	configProfileOverrideElementName OBJECT-TYPE
		SYNTAX OCTET STRING MAX-ACCESS read-only STATUS current
		DESCRIPTION "profile name, which will be referred in passpoint config."
		::= { configAnqpProfileOverrideElementEntry 1 }

	configProfileOverrideElementRowStatus OBJECT-TYPE
		SYNTAX RowStatus MAX-ACCESS read-create STATUS current
		DESCRIPTION "row addition/deletion support"
		::= { configAnqpProfileOverrideElementEntry 2 }

	configProfileOverrideElementDesc OBJECT-TYPE
		SYNTAX OCTET STRING MAX-ACCESS read-write STATUS current
		DESCRIPTION "profile description."
		::= { configAnqpProfileOverrideElementEntry 3 }

	configAnqpOverrideList OBJECT-TYPE
		SYNTAX OCTET STRING MAX-ACCESS read-write STATUS current
		DESCRIPTION "ANQP override element list."
		::= { configAnqpProfileOverrideElementEntry 4 }

configHS20ProfileOperFriendlyNameTable OBJECT-TYPE
	SYNTAX SEQUENCE OF ConfigHS20ProfileOperFriendlyNameEntry
	MAX-ACCESS not-accessible
	STATUS current
	DESCRIPTION	"List of configHS20ProfileOperFriendlyNameTable
				[FW:E2148.AC.1:X.XX.X.X]"
	::= { sc-passpoint 10 }

configHS20ProfileOperFriendlyNameEntry OBJECT-TYPE
	SYNTAX ConfigHS20ProfileOperFriendlyNameEntry
	MAX-ACCESS not-accessible
	STATUS current
	DESCRIPTION "List of configHS20ProfileOperFriendlyName
				[FW:E2148.AC.1:X.XX.X.X]"
	INDEX { configProfileOperFriendlyNameName }
	::={ configHS20ProfileOperFriendlyNameTable 1 }

ConfigHS20ProfileOperFriendlyNameEntry ::=
	SEQUENCE {
		configProfileOperFriendlyNameName OCTET STRING
		,configProfileOperFriendlyNameRowStatus RowStatus
		,configProfileOperFriendlyNameDesc OCTET STRING
		,configFriendlyNameList OCTET STRING
	}

	configProfileOperFriendlyNameName OBJECT-TYPE
		SYNTAX OCTET STRING MAX-ACCESS read-only STATUS current
		DESCRIPTION "profile name, which will be referred in passpoint config."
		::= { configHS20ProfileOperFriendlyNameEntry 1 }

	configProfileOperFriendlyNameRowStatus OBJECT-TYPE
		SYNTAX RowStatus MAX-ACCESS read-create STATUS current
		DESCRIPTION "row addition/deletion support"
		::= { configHS20ProfileOperFriendlyNameEntry 2 }

	configProfileOperFriendlyNameDesc OBJECT-TYPE
		SYNTAX OCTET STRING MAX-ACCESS read-write STATUS current
		DESCRIPTION "profile description."
		::= { configHS20ProfileOperFriendlyNameEntry 3 }

	configFriendlyNameList OBJECT-TYPE
		SYNTAX OCTET STRING MAX-ACCESS read-write STATUS current
		DESCRIPTION "List of friendly name. Format: [language 1 code]:[name 1 string];[language 2 code]:[name 2 string]"
		::= { configHS20ProfileOperFriendlyNameEntry 4 }

configHS20ProfileConnCapTable OBJECT-TYPE
	SYNTAX SEQUENCE OF ConfigHS20ProfileConnCapEntry
	MAX-ACCESS not-accessible
	STATUS current
	DESCRIPTION	"List of configHS20ProfileConnCapTable
				[FW:E2148.AC.1:X.XX.X.X]"
	::= { sc-passpoint 11 }

configHS20ProfileConnCapEntry OBJECT-TYPE
	SYNTAX ConfigHS20ProfileConnCapEntry
	MAX-ACCESS not-accessible
	STATUS current
	DESCRIPTION "List of configHS20ProfileConnCap
				[FW:E2148.AC.1:X.XX.X.X]"
	INDEX { configProfileConnCapName }
	::={ configHS20ProfileConnCapTable 1 }

ConfigHS20ProfileConnCapEntry ::=
	SEQUENCE {
		configProfileConnCapName OCTET STRING
		,configProfileConnCapRowStatus RowStatus
		,configProfileConnCapDesc OCTET STRING
		,configConnCapabList OCTET STRING
	}

	configProfileConnCapName OBJECT-TYPE
		SYNTAX OCTET STRING MAX-ACCESS read-only STATUS current
		DESCRIPTION "profile name, which will be referred in passpoint config."
		::= { configHS20ProfileConnCapEntry 1 }

	configProfileConnCapRowStatus OBJECT-TYPE
		SYNTAX RowStatus MAX-ACCESS read-create STATUS current
		DESCRIPTION "row addition/deletion support"
		::= { configHS20ProfileConnCapEntry 2 }

	configProfileConnCapDesc OBJECT-TYPE
		SYNTAX OCTET STRING MAX-ACCESS read-write STATUS current
		DESCRIPTION "profile description."
		::= { configHS20ProfileConnCapEntry 3 }

	configConnCapabList OBJECT-TYPE
		SYNTAX OCTET STRING MAX-ACCESS read-write STATUS current
		DESCRIPTION "Connection capability list."
		::= { configHS20ProfileConnCapEntry 4 }

configHS20ProfileWanMetricsTable OBJECT-TYPE
	SYNTAX SEQUENCE OF ConfigHS20ProfileWanMetricsEntry
	MAX-ACCESS not-accessible
	STATUS current
	DESCRIPTION	"List of configHS20ProfileWanMetricsTable
				[FW:E2148.AC.1:X.XX.X.X]"
	::= { sc-passpoint 12 }

configHS20ProfileWanMetricsEntry OBJECT-TYPE
	SYNTAX ConfigHS20ProfileWanMetricsEntry
	MAX-ACCESS not-accessible
	STATUS current
	DESCRIPTION "List of configHS20ProfileWanMetrics
				[FW:E2148.AC.1:X.XX.X.X]"
	INDEX { configProfileWanMetricsName }
	::={ configHS20ProfileWanMetricsTable 1 }

ConfigHS20ProfileWanMetricsEntry ::=
	SEQUENCE {
		configProfileWanMetricsName OCTET STRING
		,configProfileWanMetricsRowStatus RowStatus
		,configProfileWanMetricsDesc OCTET STRING
		,configLinkStatus INTEGER
		,configSymmetric DisableEnable
		,configAtCapacity DisableEnable
		,configDownSpeed INTEGER
		,configUpSpeed INTEGER
		,configDownLoad INTEGER
		,configUpLoad INTEGER
		,configLMD INTEGER
	}

	configProfileWanMetricsName OBJECT-TYPE
		SYNTAX OCTET STRING MAX-ACCESS read-only STATUS current
		DESCRIPTION "profile name, which will be referred in passpoint config."
		::= { configHS20ProfileWanMetricsEntry 1 }

	configProfileWanMetricsRowStatus OBJECT-TYPE
		SYNTAX RowStatus MAX-ACCESS read-create STATUS current
		DESCRIPTION "row addition/deletion support"
		::= { configHS20ProfileWanMetricsEntry 2 }

	configProfileWanMetricsDesc OBJECT-TYPE
		SYNTAX OCTET STRING MAX-ACCESS read-write STATUS current
		DESCRIPTION "profile description."
		::= { configHS20ProfileWanMetricsEntry 3 }

	configLinkStatus OBJECT-TYPE
		SYNTAX INTEGER MAX-ACCESS read-write STATUS current
		DESCRIPTION "Link status."
		::= { configHS20ProfileWanMetricsEntry 4 }

	configSymmetric OBJECT-TYPE
		SYNTAX DisableEnable MAX-ACCESS read-write STATUS current
		DESCRIPTION "Link symmetric."
		::= { configHS20ProfileWanMetricsEntry 5 }

	configAtCapacity OBJECT-TYPE
		SYNTAX DisableEnable MAX-ACCESS read-write STATUS current
		DESCRIPTION "Link at capacity."
		::= { configHS20ProfileWanMetricsEntry 6 }

	configDownSpeed OBJECT-TYPE
		SYNTAX INTEGER MAX-ACCESS read-write STATUS current
		DESCRIPTION "Down link speed in kbps."
		::= { configHS20ProfileWanMetricsEntry 7 }

	configUpSpeed OBJECT-TYPE
		SYNTAX INTEGER MAX-ACCESS read-write STATUS current
		DESCRIPTION "Up link speed in kbps."
		::= { configHS20ProfileWanMetricsEntry 8 }

	configDownLoad OBJECT-TYPE
		SYNTAX INTEGER MAX-ACCESS read-write STATUS current
		DESCRIPTION "Current load of downlink WAN connection in percentage."
		::= { configHS20ProfileWanMetricsEntry 9 }

	configUpLoad OBJECT-TYPE
		SYNTAX INTEGER MAX-ACCESS read-write STATUS current
		DESCRIPTION "Current load of uplink WAN connection in percentage."
		::= { configHS20ProfileWanMetricsEntry 10 }

	configLMD OBJECT-TYPE
		SYNTAX INTEGER MAX-ACCESS read-write STATUS current
		DESCRIPTION "Duration for measuring downlink/uplink load in millisecond; 0 if load cannot be determined."
		::= { configHS20ProfileWanMetricsEntry 11 }

configHS20ProfileOperClassTable OBJECT-TYPE
	SYNTAX SEQUENCE OF ConfigHS20ProfileOperClassEntry
	MAX-ACCESS not-accessible
	STATUS current
	DESCRIPTION	"List of configHS20ProfileOperClassTable
				[FW:E2148.AC.1:X.XX.X.X]"
	::= { sc-passpoint 13 }

configHS20ProfileOperClassEntry OBJECT-TYPE
	SYNTAX ConfigHS20ProfileOperClassEntry
	MAX-ACCESS not-accessible
	STATUS current
	DESCRIPTION "List of configHS20ProfileOperClass
				[FW:E2148.AC.1:X.XX.X.X]"
	INDEX { configProfileOperClassName }
	::={ configHS20ProfileOperClassTable 1 }

ConfigHS20ProfileOperClassEntry ::=
	SEQUENCE {
		configProfileOperClassName OCTET STRING
		,configProfileOperClassRowStatus RowStatus
		,configProfileOperClassDesc OCTET STRING
		,configOperClassList OCTET STRING
	}

	configProfileOperClassName OBJECT-TYPE
		SYNTAX OCTET STRING MAX-ACCESS read-only STATUS current
		DESCRIPTION "profile name, which will be referred in passpoint config."
		::= { configHS20ProfileOperClassEntry 1 }

	configProfileOperClassRowStatus OBJECT-TYPE
		SYNTAX RowStatus MAX-ACCESS read-create STATUS current
		DESCRIPTION "row addition/deletion support"
		::= { configHS20ProfileOperClassEntry 2 }

	configProfileOperClassDesc OBJECT-TYPE
		SYNTAX OCTET STRING MAX-ACCESS read-write STATUS current
		DESCRIPTION "profile description."
		::= { configHS20ProfileOperClassEntry 3 }

	configOperClassList OBJECT-TYPE
		SYNTAX OCTET STRING MAX-ACCESS read-write STATUS current
		DESCRIPTION "Operating class list"
		::= { configHS20ProfileOperClassEntry 4 }

configHS20ProfileOsuProviderTable OBJECT-TYPE
	SYNTAX SEQUENCE OF ConfigHS20ProfileOsuProviderEntry
	MAX-ACCESS not-accessible
	STATUS current
	DESCRIPTION	"List of configHS20ProfileOsuProviderTable
				[FW:E2148.AC.1:X.XX.X.X]"
	::= { sc-passpoint 14 }

configHS20ProfileOsuProviderEntry OBJECT-TYPE
	SYNTAX ConfigHS20ProfileOsuProviderEntry
	MAX-ACCESS not-accessible
	STATUS current
	DESCRIPTION "List of configHS20ProfileOsuProvider
				[FW:E2148.AC.1:X.XX.X.X]"
	INDEX { configProfileOsuProviderName }
	::={ configHS20ProfileOsuProviderTable 1 }

ConfigHS20ProfileOsuProviderEntry ::=
	SEQUENCE {
		configProfileOsuProviderName OCTET STRING
		,configProfileOsuProviderRowStatus RowStatus
		,configProfileOsuProviderDesc OCTET STRING
		,configOsuServerUri OCTET STRING
		,configOsuFriendlyNameList OCTET STRING
		,configOsuNai OCTET STRING
		,configOsuOmaDm DisableEnable
		,configOsuSoapXml DisableEnable
		,configOsuIconProfileList OCTET STRING
		,configOsuServiceDescList OCTET STRING
	}

	configProfileOsuProviderName OBJECT-TYPE
		SYNTAX OCTET STRING MAX-ACCESS read-only STATUS current
		DESCRIPTION "profile name, which will be referred in passpoint config."
		::= { configHS20ProfileOsuProviderEntry 1 }

	configProfileOsuProviderRowStatus OBJECT-TYPE
		SYNTAX RowStatus MAX-ACCESS read-create STATUS current
		DESCRIPTION "row addition/deletion support"
		::= { configHS20ProfileOsuProviderEntry 2 }

	configProfileOsuProviderDesc OBJECT-TYPE
		SYNTAX OCTET STRING MAX-ACCESS read-write STATUS current
		DESCRIPTION "profile description."
		::= { configHS20ProfileOsuProviderEntry 3 }

	configOsuServerUri OBJECT-TYPE
		SYNTAX OCTET STRING MAX-ACCESS read-write STATUS current
		DESCRIPTION "OSU server URI."
		::= { configHS20ProfileOsuProviderEntry 4 }

	configOsuFriendlyNameList OBJECT-TYPE
		SYNTAX OCTET STRING MAX-ACCESS read-write STATUS current
		DESCRIPTION "OSU provider friendly name list."
		::= { configHS20ProfileOsuProviderEntry 5 }

	configOsuNai OBJECT-TYPE
		SYNTAX OCTET STRING MAX-ACCESS read-write STATUS current
		DESCRIPTION "OSU NAI."
		::= { configHS20ProfileOsuProviderEntry 6 }

	configOsuOmaDm OBJECT-TYPE
		SYNTAX DisableEnable MAX-ACCESS read-write STATUS current
		DESCRIPTION "Support OMA DM(Open Mobile Alliance Device Management)."
		::= { configHS20ProfileOsuProviderEntry 7 }

	configOsuSoapXml OBJECT-TYPE
		SYNTAX DisableEnable MAX-ACCESS read-write STATUS current
		DESCRIPTION "Supoort SOAP(Simple Object Access Protocol) XML."
		::= { configHS20ProfileOsuProviderEntry 8 }

	configOsuIconProfileList OBJECT-TYPE
		SYNTAX OCTET STRING MAX-ACCESS read-write STATUS current
		DESCRIPTION "Icon profile list."
		::= { configHS20ProfileOsuProviderEntry 9 }

	configOsuServiceDescList OBJECT-TYPE
		SYNTAX OCTET STRING MAX-ACCESS read-write STATUS current
		DESCRIPTION "Service description list."
		::= { configHS20ProfileOsuProviderEntry 10 }


configProfileIconTable OBJECT-TYPE
	SYNTAX SEQUENCE OF ConfigProfileIconEntry
	MAX-ACCESS not-accessible
	STATUS current
	DESCRIPTION	"List of configProfileIconTable
				[FW:E2148.AC.1:X.XX.X.X]"
	::= { sc-passpoint 15 }

configProfileIconEntry OBJECT-TYPE
	SYNTAX ConfigProfileIconEntry
	MAX-ACCESS not-accessible
	STATUS current
	DESCRIPTION "List of configProfileIcon
				[FW:E2148.AC.1:X.XX.X.X]"
	INDEX { configProfileIconName }
	::={ configProfileIconTable 1 }

ConfigProfileIconEntry ::=
	SEQUENCE {
		configProfileIconName OCTET STRING
		,configProfileIconRowStatus RowStatus
		,configProfileIconDesc OCTET STRING
		,configIconLang OCTET STRING
		,configIconSize OCTET STRING
		,configIconType OCTET STRING
		,configIconPath OCTET STRING
		,configIconFileContent OCTET STRING
	}

	configProfileIconName OBJECT-TYPE
		SYNTAX OCTET STRING MAX-ACCESS read-only STATUS current
		DESCRIPTION "profile name, which will be referred in passpoint config."
		::= { configProfileIconEntry 1 }

	configProfileIconRowStatus OBJECT-TYPE
		SYNTAX RowStatus MAX-ACCESS read-create STATUS current
		DESCRIPTION "row addition/deletion support"
		::= { configProfileIconEntry 2 }

	configProfileIconDesc OBJECT-TYPE
		SYNTAX OCTET STRING MAX-ACCESS read-write STATUS current
		DESCRIPTION "profile description."
		::= { configProfileIconEntry 3 }

	configIconLang OBJECT-TYPE
		SYNTAX OCTET STRING MAX-ACCESS read-write STATUS current
		DESCRIPTION "Language in which the icon will be shown."
		::= { configProfileIconEntry 4 }

	configIconSize OBJECT-TYPE
		SYNTAX OCTET STRING MAX-ACCESS read-write STATUS current
		DESCRIPTION "Icon size in pixel. <Icon Width>:<Icon Height>"
		::= { configProfileIconEntry 5 }

	configIconType OBJECT-TYPE
		SYNTAX OCTET STRING MAX-ACCESS read-write STATUS current
		DESCRIPTION "MIME type of the icon file."
		::= { configProfileIconEntry 6 }

	configIconPath OBJECT-TYPE
		SYNTAX OCTET STRING MAX-ACCESS read-only STATUS current
		DESCRIPTION "Internal path of icon file."
		::= { configProfileIconEntry 7 }

	configIconFileContent OBJECT-TYPE
		SYNTAX OCTET STRING MAX-ACCESS read-write STATUS current
		DESCRIPTION "File content encoded in base64"
		::= { configProfileIconEntry 8 }
-- Service Passpoint }

-- async sysupgrade {

configAsyncUpgradeDoUpgrade OBJECT-TYPE
	SYNTAX INTEGER {
		execute(2)
	}
	MAX-ACCESS read-write
	STATUS current
	DESCRIPTION "Execute system upgrade immediately if there is a valid firmware uploaded.
				[FW:E2148.AC.1:4.16.0.1]"
	::= { sc-async-sysupgrade 1 }

configAsyncUpgradeTimerEnable OBJECT-TYPE
	SYNTAX DisableEnable
	MAX-ACCESS read-write
	STATUS current
	DESCRIPTION "Enable / disable the timer for system upgrade.
				[FW:E2148.AC.1:4.16.0.1]"
	::= { sc-async-sysupgrade 2 }

configAsyncUpgradeTimerMode OBJECT-TYPE
	SYNTAX INTEGER {
		no-retry(1),
		retry-immediately(2),
		retry-after-24h(3),
		missed-upgrade-retry-after-24h(100)
	}
	MAX-ACCESS read-write
	STATUS current
	DESCRIPTION "Current timer mode. (Mode [Repeating-applied] cannot be set, it's get-only.)
				[FW:E2148.AC.1:4.16.0.1]"
	::= { sc-async-sysupgrade 3 }

configAsyncUpgradeTimerMinute OBJECT-TYPE
	SYNTAX INTEGER
	MAX-ACCESS read-write
	STATUS current
	DESCRIPTION "Set minutes after [apply], system upgrade will be performed.
				[FW:E2148.AC.1:4.16.0.1]"
	::= { sc-async-sysupgrade 4 }

-- async sysupgrade }

-- serviceConfiguration (config files state) }

-- ===========================================
-- notifications (SNMP traps) {
--
notification OBJECT IDENTIFIER ::= { acksys 11 }

linkAlarm NOTIFICATION-TYPE
	OBJECTS { nbEventName }
	STATUS current
	DESCRIPTION "Ethernet or Wi-Fi link alarm (up or down)
		     [FW:E2148.AC.1:2.8.0.1]"
	::= { notification 1 }

powerAlarm NOTIFICATION-TYPE
	OBJECTS { nbEventName }
	STATUS current
	DESCRIPTION "Power supply alarm. Only on products with 2 power supplies
		     [FW:E2148.AC.1:2.8.0.1]"
	::= { notification 3 }

digitalInputAlarm NOTIFICATION-TYPE
	OBJECTS { nbEventName }
	STATUS current
	DESCRIPTION "Digital input alarm. Only on products with digital input
		     [FW:E2148.AC.1:2.8.0.1]"
	::= { notification 4 }

tempExceededAlarm NOTIFICATION-TYPE
	OBJECTS { nbEventName }
	STATUS current
	DESCRIPTION "Temperature alarm. The temperature exceeds the given trigger
		     [FW:E2148.AC.1:2.8.0.1]"
	::= { notification 5 }

clientLinkAlarm NOTIFICATION-TYPE
	OBJECTS { nbClientMacAddress, nbSsid, nbBssid, nbEventState, nbEventName }
	STATUS current
	DESCRIPTION "In AP mode, client was connected / disconnected
		     [FW:E2148.AC.1:2.8.0.1]"
	::= { notification 6 }

vrrpAlarm NOTIFICATION-TYPE
	OBJECTS { nbEventName }
	STATUS current
	DESCRIPTION "VRRP state change
		    [FW:E2148.AC.1:2.8.0.1]"
	::= { notification 7 }

dfsAlarm NOTIFICATION-TYPE
	OBJECTS { nbEventName }
	STATUS current
	DESCRIPTION "DFS alarm
		    [FW:E2148.AC.1:2.8.0.1]"
	::= { notification 8 }

pingerAlarm NOTIFICATION-TYPE
	OBJECTS { nbEventName }
	STATUS current
	DESCRIPTION "Notified if the hostname do not respond to the ping
		    [FW:E2148.AC.1:2.8.0.1]"
	::= { notification 9 }

tcnAlarm NOTIFICATION-TYPE
	OBJECTS { nbEventName }
	STATUS current
	DESCRIPTION "TCN state change alarm"
	::= { notification 11 }

securityAlarm NOTIFICATION-TYPE
	OBJECTS { nbEventName }
	STATUS current
	DESCRIPTION "Security-related alarm"
	::= { notification 12 }

-- notifications (SNMP traps) }
-- ===========================================
-- notificationBindings (SNMP traps) variables bound in notifications {
--
notificationBindings OBJECT IDENTIFIER ::= { notification 255 }

nbClientMacAddress OBJECT-TYPE
	SYNTAX PhysAddress
	MAX-ACCESS accessible-for-notify
	STATUS current
	DESCRIPTION "MAC address of the client connected to the AP.
		     [FW:E2148.AC.1:2.8.0.1]"
	::= { notificationBindings 1 }

nbSsid OBJECT-TYPE
	SYNTAX OCTET STRING (SIZE (0..33))
	MAX-ACCESS accessible-for-notify
	STATUS current
	DESCRIPTION "The SSID for which the trap was triggered
		     [FW:E2148.AC.1:2.8.0.1]"
	::= { notificationBindings 2 }

nbBssid OBJECT-TYPE
	SYNTAX PhysAddress
	MAX-ACCESS accessible-for-notify
	STATUS current
	DESCRIPTION "The BSSID for which the trap was triggered
		Warning, a 17-bytes column-separated string may
		be returned with this OID.
		[FW:E2148.AC.1:2.8.0.1]"
	::= { notificationBindings 3 }

nbEventState OBJECT-TYPE
	SYNTAX DisplayString
	MAX-ACCESS accessible-for-notify
	STATUS current
	DESCRIPTION "Notification state. Currently, possible values are 'up', 'down',
		 'connect', 'disconnect', 'DFS_CAC_STARTED', 'DFS_CAC_FINISHED',
		 'DFS_CAC_ABORTED', 'DFS_RADAR_DETECTED', 'DFS_NOP_FINISHED'
		 [FW:E2148.AC.1:2.8.0.1]"
	::= { notificationBindings 4 }

nbEventName OBJECT-TYPE
	SYNTAX DisplayString
	MAX-ACCESS accessible-for-notify
	STATUS current
	DESCRIPTION "User-provided name of the event trigger in the product configuration database
		     [FW:E2148.AC.1:2.8.0.1]"
	::= { notificationBindings 5 }

nbRadioName OBJECT-TYPE
	SYNTAX DisplayString
	MAX-ACCESS accessible-for-notify
	STATUS current
	DESCRIPTION "Radio card name
		     [FW:E2148.AC.1:2.8.0.1]"
	::= { notificationBindings 6 }

nbRadioMacAddress OBJECT-TYPE
	SYNTAX PhysAddress
	MAX-ACCESS accessible-for-notify
	STATUS current
	DESCRIPTION "Radio card Mac address
		    [FW:E2148.AC.1:2.8.0.1]"
	::= { notificationBindings 7 }

nbRadioChannel OBJECT-TYPE
	SYNTAX Unsigned32
	MAX-ACCESS accessible-for-notify
	STATUS current
	DESCRIPTION "Current Radio channel
		     [FW:E2148.AC.1:2.8.0.1]"
	::= { notificationBindings 8 }

nbRadioChannelWidth OBJECT-TYPE
	SYNTAX Unsigned32
	MAX-ACCESS accessible-for-notify
	STATUS current
	DESCRIPTION "Current Radio channel width in Mhz
		     [FW:E2148.AC.1:2.8.0.1]"
	::= { notificationBindings 9 }

nbRadarChannel OBJECT-TYPE
	SYNTAX Unsigned32
	MAX-ACCESS accessible-for-notify
	STATUS current
	DESCRIPTION "Current Radar channel
		     [FW:E2148.AC.1:2.8.0.1]"
	::= { notificationBindings 10 }

nbRadarChannelWidth OBJECT-TYPE
	SYNTAX Unsigned32
	MAX-ACCESS accessible-for-notify
	STATUS current
	DESCRIPTION "Current Radar channel width in Mhz
		     [FW:E2148.AC.1:2.8.0.1]"
	::= { notificationBindings 11 }

nbHostName OBJECT-TYPE
	SYNTAX DisplayString
	MAX-ACCESS accessible-for-notify
	STATUS current
	DESCRIPTION "Host name of the equipment that triggered an event on the product
		     [FW:E2148.AC.1:2.8.0.1]"
	::= { notificationBindings 12 }

nbDigitalInName OBJECT-TYPE
	SYNTAX DisplayString
	MAX-ACCESS accessible-for-notify
	STATUS current
	DESCRIPTION "Digital input name
		     [FW:E2148.AC.1:3.16.0.1]"
	::= { notificationBindings 13 }

nbTcnTaiIp OBJECT-TYPE
	SYNTAX IpAddress
	MAX-ACCESS accessible-for-notify
	STATUS current
	DESCRIPTION "TCN Ip address of ETBN train application interface"
	::= { notificationBindings 14 }

nbTcnEtbnStatus OBJECT-TYPE
	SYNTAX INTEGER {
		initConfig(3),
		notInaugurated(4),
		readyForInauguration(5),
		tndValidated(6),
		inaugurating(7),
		initServices(8),
		inaugurated(9),
		interConsistOperational(10),
		tndPendingRemoval(11)
	}
	MAX-ACCESS accessible-for-notify
	STATUS current
	DESCRIPTION "TCN ETBN status"
	::= { notificationBindings 15 }

nbTcnEtbnRole OBJECT-TYPE
	SYNTAX INTEGER {
		undefined(0),
		master(1),
		backup(2),
		notRedundant(3)
	}
	MAX-ACCESS accessible-for-notify
	STATUS current
	DESCRIPTION "TCN ETBN role"
	::= { notificationBindings 16 }

nbTcnEtbnTopoCnt OBJECT-TYPE
	SYNTAX Unsigned32
	MAX-ACCESS accessible-for-notify
	STATUS current
	DESCRIPTION "TCN CRC32 of the discovered train network directory"
	::= { notificationBindings 17 }

nbTcnEtbTopoCntState OBJECT-TYPE
	SYNTAX INTEGER {
			valid(1),
			invalid(2)
		}
	MAX-ACCESS accessible-for-notify
	STATUS current
	DESCRIPTION "ETB topology count validity state: if it is invalid,
		this means that at least one ETB of the current Train
		Network Directory has left current stable topology (removed
		its TND) and has detected a different topology"
	::= { notificationBindings 18 }

nbTcnLengtheningFlag OBJECT-TYPE
	SYNTAX TruthValue
	MAX-ACCESS accessible-for-notify
	STATUS current
	DESCRIPTION "TCN lengthening flag"
	::= { notificationBindings 19 }

nbTcnShorteningState OBJECT-TYPE
	SYNTAX OCTET STRING (SIZE (8))
	MAX-ACCESS accessible-for-notify
	STATUS current
	DESCRIPTION "TCN Shortening state"
	::= { notificationBindings 20 }

nbTcnRadio1CouplingState OBJECT-TYPE
	SYNTAX INTEGER {
		stopped(0),
		scanning(1),
		signalgood(2),
		signalbad(3)
	}
	MAX-ACCESS accessible-for-notify
	STATUS current
	DESCRIPTION "TCN Radio coupling state"
	::= { notificationBindings 21 }

nbTcnConsistCount OBJECT-TYPE
	SYNTAX INTEGER (1..63)
	MAX-ACCESS accessible-for-notify
	STATUS current
	DESCRIPTION "Number of consists in the train"
	::= { notificationBindings 22 }

nbTcnConsistPosition OBJECT-TYPE
	SYNTAX INTEGER (1..63)
	MAX-ACCESS accessible-for-notify
	STATUS current
	DESCRIPTION "Consist position in the train"
	::= { notificationBindings 23 }

nbDescription OBJECT-TYPE
	SYNTAX DisplayString MAX-ACCESS accessible-for-notify STATUS current
	DESCRIPTION "Any available details about the event triggering the trap
		[FW:E2148.AC.1:4.16.0.1]"
	::= { notificationBindings 24 }

nbTimestamp OBJECT-TYPE
	SYNTAX Unsigned32 MAX-ACCESS accessible-for-notify STATUS current
	DESCRIPTION "Time of the event triggering the trap. Time is in seconds
	since the Epoch (1/1/1970 00:00 UTC) - see POSIX Base Definitions.
		[FW:E2148.AC.1:4.16.0.1]"
	::= { notificationBindings 25 }

nbMacAddr OBJECT-TYPE
	SYNTAX PhysAddress MAX-ACCESS accessible-for-notify STATUS current
	DESCRIPTION "The BSSID for which the trap was triggered
		Format is binary PhysAddr (contrary to nbBssid binding).
		[FW:E2148.AC.1:4.16.0.1]"
	::= { notificationBindings 26 }

nbSource OBJECT-TYPE
	SYNTAX DisplayString MAX-ACCESS accessible-for-notify STATUS current
	DESCRIPTION "A tag which identifies the origin of the event.
		[FW:E2148.AC.1:4.16.0.1]"
	::= { notificationBindings 27 }

-- notificationBindings (SNMP traps) }

acksysProductSerialNumber OBJECT-TYPE
	SYNTAX DisplayString
	MAX-ACCESS read-only
	STATUS current
	DESCRIPTION
		"Returns the product serial number
		[FW:E2148.AC.1:2.8.0.1]"
	::= { acksys 12 }

END
