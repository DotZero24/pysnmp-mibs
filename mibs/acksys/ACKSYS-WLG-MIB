--Acksys enterprise MIB V2.22.0
-- This MIB is compatible with SNMP V2c
-- Clean with VIM command: :g/@[GS]ET/d

ACKSYS-WLG-MIB DEFINITIONS ::= BEGIN

IMPORTS
     enterprises,mgmt, IpAddress, Counter32, Gauge32,
                TimeTicks
            FROM SNMPv2-SMI
        OBJECT-TYPE, MODULE-IDENTITY FROM SNMPv2-SMI;

--Module Identity
acksysMIB MODULE-IDENTITY
    LAST-UPDATED "201601291500Z"
    ORGANIZATION "ACKSYS Communication & Systems"
    CONTACT-INFO "support@acksys.fr"
    DESCRIPTION	 "SNMPv2C Module for ACKSYS Solutions"
    ::= { acksys 2 }

-- textual conventions

DisplayString ::=
    OCTET STRING
-- This data type is used to model textual information taken
-- from the NVT ASCII character set.  By convention, objects
-- with this syntax are declared as having

--
--      SIZE (0..255)

PhysAddress ::=
    OCTET STRING(SIZE (6))
-- This data type is used to model media addresses.  For many
-- types of media, this will be in a binary representation.
-- For example, an ethernet address would be represented as
-- a string of 6 octets.

acksys OBJECT IDENTIFIER ::= { enterprises 28097 }

-- Acksys specific MIBs.
network-product OBJECT IDENTIFIER ::= { acksys 1 }
c-key-management OBJECT IDENTIFIER ::= { acksys 4 }
alarmSettings OBJECT IDENTIFIER ::= { acksys 5 }
powerStatus OBJECT IDENTIFIER ::= { acksys 6 }

wifiInterface OBJECT IDENTIFIER ::= { network-product 1 }
administration OBJECT IDENTIFIER ::= { network-product 2 }
os-stat OBJECT IDENTIFIER ::= { network-product 3 }
productSpecific OBJECT IDENTIFIER ::= { network-product 4 }
lanInterface OBJECT IDENTIFIER ::= {network-product 5}

settings OBJECT IDENTIFIER ::= { wifiInterface 1 }
bridge-mode OBJECT IDENTIFIER ::= { wifiInterface 2 }
access-point-mode OBJECT IDENTIFIER ::= { wifiInterface 3}
advancedSettings OBJECT IDENTIFIER ::= { wifiInterface 4 }

bridgeAPFiltering OBJECT IDENTIFIER ::= { bridge-mode 8}

bridgeRoaming OBJECT IDENTIFIER ::= { bridge-mode 9}
bridgeWirelessScan OBJECT IDENTIFIER ::= { bridge-mode 11}
bridgeNAT OBJECT IDENTIFIER ::= { bridge-mode 12}
bridgeNatPortForwarding OBJECT IDENTIFIER ::= { bridgeNAT 11}

bridgeRoamingAdvanced OBJECT IDENTIFIER ::={bridgeRoaming 1}


apClientFiltering OBJECT IDENTIFIER ::= { access-point-mode 4}

securitySettings OBJECT IDENTIFIER ::= { settings 9 }
securityWEP OBJECT IDENTIFIER ::= { securitySettings 2 }
securityWPA-WPA2 OBJECT IDENTIFIER ::= { securitySettings 3}
securityPresharedKey OBJECT IDENTIFIER ::= { securityWPA-WPA2 1}
securityRadius OBJECT IDENTIFIER ::= { securityWPA-WPA2 2} --Obsolete
securityBackupRadius OBJECT IDENTIFIER ::= { securityWPA-WPA2 3} --Obsolete
securityRadiusAP OBJECT IDENTIFIER ::= { securityRadius 6}
securityRadiusBridge OBJECT IDENTIFIER ::= { securityRadius 7}
securityRadiusAPBackup OBJECT IDENTIFIER ::= { securityRadiusAP 6}
wds OBJECT IDENTIFIER ::= { access-point-mode 5}
lanTimeOutSettings OBJECT IDENTIFIER ::= { access-point-mode 8}


longDistanceSettings OBJECT IDENTIFIER ::= { advancedSettings 1}

wlg-aboard OBJECT IDENTIFIER ::= { productSpecific 1 }


alarmSettingsPower1Down OBJECT IDENTIFIER ::= { alarmSettings 2 }
alarmSettingsPower2Down OBJECT IDENTIFIER ::= { alarmSettings 3 }
alarmSettingsLan1Down OBJECT IDENTIFIER ::= { alarmSettings 4 }
alarmSettingsLan2Down OBJECT IDENTIFIER ::= { alarmSettings 5 }
alarmSettingsLan3Down OBJECT IDENTIFIER ::= { alarmSettings 6 }
alarmSettingsLan4Down OBJECT IDENTIFIER ::= { alarmSettings 7 }
alarmSettingsLan5Down OBJECT IDENTIFIER ::= { alarmSettings 8 }
alarmSettingsLan6Down OBJECT IDENTIFIER ::= { alarmSettings 9 }
alarmSettingsLan7Down OBJECT IDENTIFIER ::= { alarmSettings 10 }
alarmSettingsLan8Down OBJECT IDENTIFIER ::= { alarmSettings 11 }
alarmSettingsWLANDown OBJECT IDENTIFIER ::= { alarmSettings 12 }
--acksys group
acksysProductID OBJECT-TYPE
    SYNTAX  INTEGER {
                wlg-link(1),
                wlg-aboard-n(2),
				wlg-link-v2(3),
				wlg-aboard-n-v2(4)
            }
    MAX-ACCESS  read-only
	STATUS  current
    DESCRIPTION
            "Return the product Id code
			"
    ::= { acksys 3 }

--network-product

--Wireless Interface group
settingInterfaceSsid OBJECT-TYPE
    SYNTAX  DisplayString (SIZE (0..33))
    MAX-ACCESS  read-write
	STATUS  current
    DESCRIPTION
            "SSID (wireless network name)
	"
    ::= { settings 1 }

settingInterfaceWifiMode OBJECT-TYPE
    SYNTAX  INTEGER {
                bridge(1),
                access-point(2)
            }
    MAX-ACCESS  read-write
	STATUS  current
    DESCRIPTION
            "Select between MAX-ACCESS POINT and BRIDGE
		"
    ::= { settings 2 }

settingInterfaceChannel OBJECT-TYPE
	SYNTAX  INTEGER
	MAX-ACCESS  read-write
	STATUS  current
	DESCRIPTION
            "A wireless network uses specific channels to handle communication between clients. Some channels in your area may have interference from other electronic devices. Choose the clearest channel to help optimize the performance and coverage of your wireless network.(used in MAX-ACCESS POINT & AD-HOC BRIDGE modes)
	"
    ::= { settings 3 }

settingInterface80211Mode OBJECT-TYPE
	SYNTAX  INTEGER {
			b-only(1),
			g-only(2),
			mixed-b-g(3),
			a-only(4)
		}
	MAX-ACCESS  read-write
	STATUS  current
	DESCRIPTION
			"Select IEEE 802.11x compatibility mode.
		"
	::= { settings 4 }

settingInterfaceSuper-a-g-Mode OBJECT-TYPE
	SYNTAX  INTEGER {
			disable(1),
			super-g-without-turbo(2),
			super-g-with-static-turbo(3),
			super-g-with-dynamic-turbo(4)

		}
	MAX-ACCESS  read-write
	STATUS  current
	DESCRIPTION
			"This parameter enables the SUPER A/G mode to reach the 108 Mbits/s speed

		"
	::= { settings 5 }

settingEnableRadio OBJECT-TYPE
    SYNTAX INTEGER {
    			off(1),
			on(2)
		}
    MAX-ACCESS read-write
    STATUS current
    DESCRIPTION
    	" Enable / Disable wifi radio
	"
    ::= { settings 6 }

settingTxPoxer OBJECT-TYPE
    SYNTAX INTEGER {
    			high(1),
			medium(2),
			low(3)
		}
    MAX-ACCESS read-write
    STATUS current
    DESCRIPTION
    	" Set WIFI tx power
	"
    ::= { settings 7 }

settingRegion OBJECT-TYPE
    SYNTAX INTEGER {
			israel(2),
			usa(4),
			hong-kong(5),
			canada(6),
			australia(7),
			franceoutdoor(10),
			europe(14),
			japan(17),
			singapore(18),
			korea(20),
			mexico(21),
			indonesia(22),
			china(23),
			russia(27),
			brazil(28),
			chile(29),
			thailand(30),
			peru(31)
		}
    MAX-ACCESS read-write
    STATUS current
    DESCRIPTION
    	" Set WIFI regulation domain
	"
    ::= { settings 8 }

settingAntennaChoice OBJECT-TYPE
	SYNTAX INTEGER {
			diversity(1),
			main(2),
			aux(3)
	}
    MAX-ACCESS read-write
    STATUS current
    DESCRIPTION
    	" Set the antenna type
	"
    ::= { settings 10 }

--Setting Transmission rate
settingTransmisionRate OBJECT-TYPE
	SYNTAX INTEGER
    MAX-ACCESS read-write
    STATUS current
    DESCRIPTION
    	" Set the transmission rate in Mbps
		  Automatic : -1
		  With SuperAG Mode : 108,96,72,48,36,24,18,12
		  Without SuperAG mode : 54,48,36,24,18,12,9,6
		  802.11b mode : 11,5.5,2,1
	"
    ::= { settings 11 }


--Setting flag udap sans password
settingFlagUdapnopassword OBJECT-TYPE
	SYNTAX INTEGER {
			false(1),
			true(2)
			}
	MAX-ACCESS read-write
	STATUS current
	DESCRIPTION
		"Configure LAN settings without password
		"
	::= { settings 12 }
--Setting filter in same net
settingFlagFiltersamenet OBJECT-TYPE
	SYNTAX INTEGER {
			disable(1),
			different-subnet-filter(2),
			custom-subnet-filter(3)
			}
	MAX-ACCESS read-write
	STATUS current
	DESCRIPTION
		"Subnet filter settings:
		    (1) Disable the filter,
		    (2) Different subnet filter: drop all packets on the different subnet,
		    (3) Custom subnet filter: drop all packets on the custom subnet (You need to define IP and subnet mask of custom subnet.)
		"
	::= { settings 13 }
--Setting economy filter
settingFlagFilterframecosom OBJECT-TYPE
	SYNTAX INTEGER {
			false(1),
			true(2)
			}
	MAX-ACCESS read-write
	STATUS current
	DESCRIPTION
		"Setting economy filter
		"
	::= { settings 14 }

--Setting DFS support
settingDFSsupport OBJECT-TYPE
	SYNTAX INTEGER {
			false(1),
			true(2)
			}
	MAX-ACCESS read-write
	STATUS current
	DESCRIPTION
		"Setting DFS support
		"
	::= { settings 15 }
settingFilterCustomIpAddr OBJECT-TYPE
    SYNTAX  IpAddress
    MAX-ACCESS read-write
    STATUS current
    DESCRIPTION
            "
		Set IP address of custom subnet.

		When settingFlagFiltersamenet is set on '(3) Custom subnet filter', you need to define custom subnet.
		All packets on the custom subnet will be dropped.
		"
    ::= { settings 16 }
settingFilterCustomSubnetMask OBJECT-TYPE
    SYNTAX  IpAddress
    MAX-ACCESS read-write
    STATUS current
    DESCRIPTION
            "Set subnet mask of custom subnet.

	     When settingFlagFiltersamenet is set on '(3) Custom subnet filter', you need to define custom subnet.
	     All packets on the custom subnet will be dropped.
		"
    ::= { settings 17 }
-- Advanced setting group
enable802-11d OBJECT-TYPE
	SYNTAX INTEGER {
		disable(1),
		enable(2)
	}
    MAX-ACCESS read-write
    STATUS current
    DESCRIPTION
    	" Enable / disable the 802.11d.
	"
    ::= { advancedSettings 2 }
enableIsolateSTA OBJECT-TYPE
	SYNTAX INTEGER {
		disable(1),
		enable(2)
	}
    MAX-ACCESS read-write
    STATUS current
    DESCRIPTION
    	" Enable / disable the isolating access point.
	"
    ::= { advancedSettings 3 }

-- long distance settings groups
enableLongDistance OBJECT-TYPE
	SYNTAX INTEGER {
		disable(1),
		enable(2)
	}
    MAX-ACCESS read-write
    STATUS current
    DESCRIPTION
    	" Enable / disable distance parameter.
	"
    ::= { longDistanceSettings 1 }

distanceAntennaMeter OBJECT-TYPE
	SYNTAX INTEGER
    MAX-ACCESS read-write
    STATUS current
    DESCRIPTION
    	" Set the distance between antenna in meter.
	"
    ::= { longDistanceSettings 2 }

distanceSlotTime OBJECT-TYPE
	SYNTAX INTEGER
    MAX-ACCESS read-write
    STATUS current
    DESCRIPTION
    	"
	"
    ::= { longDistanceSettings 3 }

distanceAckTimeout OBJECT-TYPE
	SYNTAX INTEGER
    MAX-ACCESS read-write
    STATUS current
    DESCRIPTION
    	"
	"
    ::= { longDistanceSettings 4 }

distanceCtsTimeout OBJECT-TYPE
	SYNTAX INTEGER
    MAX-ACCESS read-write
    STATUS current
    DESCRIPTION
    	"
	"
    ::= { longDistanceSettings 5 }

--Setting security group
securityMode OBJECT-TYPE
    SYNTAX INTEGER {
    		none(1),
			wep(2),
			wpa-wpa2-psk(3),
			wpa-wpa2(4)
		}
    MAX-ACCESS read-write
    STATUS current
    DESCRIPTION
    	" Set the security mode
	"
    ::= { securitySettings 1 }

--WEP group
securityModeWepKeyLen OBJECT-TYPE
    SYNTAX INTEGER
    MAX-ACCESS read-write
    STATUS current
    DESCRIPTION
            "Set the WEP key len (64 bits or 128 bits)
		"
    ::= { securityWEP 1 }

securityModeWepKey-1 OBJECT-TYPE
    SYNTAX   OCTET STRING (SIZE (0..26))
    MAX-ACCESS read-write
    STATUS current
    DESCRIPTION
            "WEP key 1 in hexadecimal format
		"
    ::= { securityWEP 2 }

securityModeWepKey-2 OBJECT-TYPE
    SYNTAX  OCTET STRING (SIZE (0..26))
    MAX-ACCESS read-write
    STATUS current
    DESCRIPTION
            "WEP key 2 in hexadecimal format
		"
    ::= { securityWEP 3 }

securityModeWepKey-3 OBJECT-TYPE
    SYNTAX  OCTET STRING (SIZE (0..26))
    MAX-ACCESS read-write
    STATUS current
    DESCRIPTION
            "WEP key 3 in hexadecimal format
		"
    ::= { securityWEP 4 }

securityModeWepKey-4 OBJECT-TYPE
    SYNTAX  OCTET STRING (SIZE (0..26))
    MAX-ACCESS read-write
    STATUS current
    DESCRIPTION
            "WEP key 4 in hexadecimal format
		"
    ::= { securityWEP 5 }

securityModeDefaultWepKey OBJECT-TYPE
    SYNTAX INTEGER
    MAX-ACCESS read-write
    STATUS current
    DESCRIPTION
            "Set the wep key used
		"
    ::= { securityWEP 6 }

securityModeWepAuthentication OBJECT-TYPE
    SYNTAX INTEGER {
		open(1),
		shared(2)
	}
    MAX-ACCESS read-write
    STATUS current
    DESCRIPTION
            "Set WEP Authentication
		"
    ::= { securityWEP 7 }

--WPA/WPA2-PSK group

securityModeWpaMode OBJECT-TYPE
    SYNTAX INTEGER {
		wpa(1),
		wpa2(2)
	}
    MAX-ACCESS read-write
    STATUS current
    DESCRIPTION
            "Select the wpa mode
		"
    ::= { securityWPA-WPA2 4 }

securityModeWpaCipherType OBJECT-TYPE
    SYNTAX INTEGER {
		tkip(1),
		aes(2)
	}
    MAX-ACCESS read-write
    STATUS current
    DESCRIPTION
            "select the cipher type
		"
    ::= { securityWPA-WPA2 5 }

securityModeWpaKeyUpdateInterval OBJECT-TYPE
    SYNTAX INTEGER
    MAX-ACCESS read-write
    STATUS current
    DESCRIPTION
            "Set the group key interval
		"
    ::= { securityWPA-WPA2 6 }

--Pre-shared key group
securityModeWpaPresharedKey OBJECT-TYPE
    SYNTAX OCTET STRING (SIZE (8..64))
    MAX-ACCESS read-write
    STATUS current
    DESCRIPTION
            "Set the group key interval
			"
    ::= { securityPresharedKey 1 }

-- radius AP
securityModeWPARadiusAPAuthenticationTimeout OBJECT-TYPE
	SYNTAX INTEGER
    MAX-ACCESS read-write
    STATUS current
    DESCRIPTION
            "Set the group key interval
			"
    ::= { securityRadiusAP 1 }

securityModeWPARadiusAPIP OBJECT-TYPE
	SYNTAX  IpAddress
    MAX-ACCESS read-write
    STATUS current
    DESCRIPTION
            "Set the group key interval
			"
    ::= { securityRadiusAP 2 }

securityModeWPARadiusAPPort OBJECT-TYPE
	SYNTAX  INTEGER
    MAX-ACCESS read-write
    STATUS current
    DESCRIPTION
            "Set the group key interval
			"
    ::= { securityRadiusAP 3 }

securityModeWPARadiusAPSecret OBJECT-TYPE
	SYNTAX OCTET STRING (SIZE (1..64))
    MAX-ACCESS read-write
    STATUS current
    DESCRIPTION
            "Set the group key interval
			"
    ::= { securityRadiusAP 4 }

securityModeWPARadiusAPMacAddressAuthentication OBJECT-TYPE
	SYNTAX INTEGER {
		disable(1),
		enable(2)
		}
    MAX-ACCESS read-write
    STATUS current
    DESCRIPTION
            "Set the group key interval
			"
    ::= { securityRadiusAP 5 }
--Obsolete OIDs
securityModeWPARadiusAuthenticationTimeout OBJECT-TYPE
	SYNTAX INTEGER
    MAX-ACCESS read-write
    STATUS obsolete
    DESCRIPTION
            "Set the group key interval
			"
    ::= { securityRadius 1 }

securityModeWPARadiusIP OBJECT-TYPE
	SYNTAX  IpAddress
    MAX-ACCESS read-write
    STATUS obsolete
    DESCRIPTION
            "Set the group key interval
			"
    ::= { securityRadius 2 }

securityModeWPARadiusPort OBJECT-TYPE
	SYNTAX  INTEGER
    MAX-ACCESS read-write
    STATUS obsolete
    DESCRIPTION
            "Set the group key interval
			"
    ::= { securityRadius 3 }

securityModeWPARadiusSecret OBJECT-TYPE
	SYNTAX OCTET STRING (SIZE (1..64))
    MAX-ACCESS read-write
    STATUS obsolete
    DESCRIPTION
            "Set the group key interval
			"
    ::= { securityRadius 4 }

securityModeWPARadiusMacAddressAuthentication OBJECT-TYPE
	SYNTAX INTEGER {
		disable(1),
		enable(2)
		}
    MAX-ACCESS read-write
    STATUS obsolete
    DESCRIPTION
            "Set the group key interval
			"
    ::= { securityRadius 5 }
--End of Obsolete OIDs

-- backup radius
securityModeWPABackupRadiusAPIP OBJECT-TYPE
	SYNTAX  IpAddress
    MAX-ACCESS read-write
    STATUS current
    DESCRIPTION
            "Set the group key interval
			"
    ::= { securityRadiusAPBackup 1 }

securityModeWPARadiusBackupAPPort OBJECT-TYPE
	SYNTAX  INTEGER
    MAX-ACCESS read-write
    STATUS current
    DESCRIPTION
            "Set the group key interval
			"
    ::= { securityRadiusAPBackup 2 }

securityModeWPARadiusBackupAPSecret OBJECT-TYPE
	SYNTAX OCTET STRING (SIZE (1..64))
    MAX-ACCESS read-write
    STATUS current
    DESCRIPTION
            "Set the group key interval
			"
    ::= { securityRadiusAPBackup 3 }

securityModeWPABackupRadiusAPMacAddressAuthentication OBJECT-TYPE
	SYNTAX INTEGER {
		disable(1),
		enable(2)
		}
    MAX-ACCESS read-write
    STATUS current
    DESCRIPTION
            "Set the group key interval
		"
    ::= { securityRadiusAPBackup 4 }

--Obsolete OIDs
securityModeWPABackupRadiusIP OBJECT-TYPE
	SYNTAX  IpAddress
    MAX-ACCESS read-write
    STATUS obsolete
    DESCRIPTION
            "Set the group key interval
			"
    ::= { securityBackupRadius 1 }

securityModeWPARadiusBackupPort OBJECT-TYPE
	SYNTAX  INTEGER
    MAX-ACCESS read-write
    STATUS obsolete
    DESCRIPTION
            "Set the group key interval
			"
    ::= { securityBackupRadius 2 }

securityModeWPARadiusBackupSecret OBJECT-TYPE
	SYNTAX OCTET STRING (SIZE (1..64))
    MAX-ACCESS read-write
    STATUS obsolete
    DESCRIPTION
            "Set the group key interval
			"
    ::= { securityBackupRadius 3 }

securityModeWPABackupRadiusMacAddressAuthentication OBJECT-TYPE
	SYNTAX INTEGER {
		disable(1),
		enable(2)
		}
    MAX-ACCESS read-write
    STATUS obsolete
    DESCRIPTION
            "Set the group key interval
		"
    ::= { securityBackupRadius 4 }
--End of Obsolete OIDs

-- radius Bridge
securityModeWPARadiusLogin OBJECT-TYPE
	SYNTAX OCTET STRING (SIZE (1..64))
    MAX-ACCESS read-write
    STATUS current
    DESCRIPTION
            "Set the group key interval
			"
    ::= { securityRadiusBridge 1 }

securityModeWPARadiusPassword OBJECT-TYPE
	SYNTAX OCTET STRING (SIZE (1..64))
    MAX-ACCESS read-write
    STATUS current
    DESCRIPTION
            "Set the group key interval
			"
    ::= { securityRadiusBridge 2 }


--Access point group
apClientTable OBJECT-TYPE
    SYNTAX  SEQUENCE OF ApClientEntry
    MAX-ACCESS  not-accessible
    STATUS  current
    DESCRIPTION
            "Significant only in MAX-ACCESS POINT mode. This table shows information about connected clients."
    ::= { access-point-mode 1 }

apAutomaticChannel OBJECT-TYPE
    SYNTAX INTEGER {
			off(1),
			on(2)
		}
    MAX-ACCESS read-write
    STATUS current
    DESCRIPTION
    	" Enable / disable the automatic channel select
	"
    ::= { access-point-mode 2}

apClientCount OBJECT-TYPE
    SYNTAX INTEGER
    MAX-ACCESS read-only
    STATUS current
    DESCRIPTION
    	" count the number of entries in ApClientEntry
	"
    ::= { access-point-mode 3}

apClientEntry OBJECT-TYPE
    SYNTAX  ApClientEntry
    MAX-ACCESS  not-accessible
    STATUS  current
    DESCRIPTION
            "Shows information about the connected client.
	"
    INDEX   { clientMacAddr }
    ::= { apClientTable 1 }

ApClientEntry ::=
    SEQUENCE {
        clientMacAddr
            PhysAddress,
        client80211Mode
			INTEGER,
		clientTxRate
			INTEGER ,
		clientRssiPercent
			Gauge32
	}

clientMacAddr OBJECT-TYPE
    SYNTAX PhysAddress
    MAX-ACCESS read-only
    STATUS current
    DESCRIPTION
            "MAC address of the client connected to the MAX-ACCESS POINT."
    ::= { apClientEntry 1 }

client80211Mode OBJECT-TYPE
    SYNTAX INTEGER {
		b-only(1),
		g-only(2),
		mixed-b-g(3),
		a-only(4)
    }
    MAX-ACCESS read-only
    STATUS current
    DESCRIPTION
            "Show client's IEEE 802.11x compatibility mode."
    ::= { apClientEntry 2 }

clientTxRate OBJECT-TYPE
    SYNTAX INTEGER
    MAX-ACCESS read-only
    STATUS current
    DESCRIPTION
            "Client's communication speed in bits per second"
    ::= { apClientEntry 3 }

clientRssiPercent OBJECT-TYPE
    SYNTAX Gauge32
    MAX-ACCESS read-only
    STATUS current
    DESCRIPTION
            "Client's RSSI (percent)"
    ::= { apClientEntry 4}

settingSSIDVisibility OBJECT-TYPE
	SYNTAX INTEGER {
			visible(2),
			invisible(1)
	}
    MAX-ACCESS read-write
    STATUS current
    DESCRIPTION
    	" Enable or Disable SSID Visibility
	"
    ::= { access-point-mode 6}

enableSTP OBJECT-TYPE
	SYNTAX INTEGER {
		disable(1),
		enable(2)
	}
    MAX-ACCESS read-write
    STATUS current
    DESCRIPTION
    	" Enable / disable STP protocol.
	"
    ::= { access-point-mode 7 }

enableLanTimeout OBJECT-TYPE
	SYNTAX INTEGER {
		disable(1),
		enable(2)
	}
    MAX-ACCESS read-write
    STATUS current
    DESCRIPTION
    	" Enable / disable LAN timeout.
			ACCESS POINT can be configured to auto-disconnect the radio when the LAN is disconnected from the equipment.

	"
    ::= { lanTimeOutSettings 1 }

lanTimeoutIPSurvey OBJECT-TYPE
	SYNTAX INTEGER
    MAX-ACCESS read-write
    STATUS current
    DESCRIPTION
		"
		    Define the IP address where the probe was be sent.

	"
    ::= { lanTimeOutSettings 2 }

lanTimeoutMaxProbe OBJECT-TYPE
	SYNTAX INTEGER
    MAX-ACCESS read-write
    STATUS current
    DESCRIPTION
		"
		   Define the number of probe without response necessairy to disconnect the radio.

	"
    ::= { lanTimeOutSettings 3 }

lanTimeoutProbeTimeout OBJECT-TYPE
	SYNTAX INTEGER
    MAX-ACCESS read-write
    STATUS current
    DESCRIPTION
		"
		  Define the probe response waiting time in seconds.

	"
    ::= { lanTimeOutSettings 4 }

lanTimeoutProbeInterval OBJECT-TYPE
	SYNTAX INTEGER
    MAX-ACCESS read-write
    STATUS current
    DESCRIPTION
		"
		 Define the times in seconds between each probes.

	"
    ::= { lanTimeOutSettings 5 }


------------------------
--AP Filtering

apClientFilteringEnable OBJECT-TYPE
	SYNTAX  INTEGER {
			off(1),
          on(2)
		}
	MAX-ACCESS  read-write
	STATUS  current
	DESCRIPTION "Enable / Disable Client Filtering.
		"
	::= { apClientFiltering 1 }

apClientFilteringMode OBJECT-TYPE
	SYNTAX  INTEGER {
			allow(1),
          deny(2)
		}
	MAX-ACCESS  read-write
	STATUS  current
	DESCRIPTION "Select Client Filtering Mode (allow/Deny)
		"
	::= { apClientFiltering 2 }

apClientWirelessFiltering OBJECT-TYPE
	SYNTAX  INTEGER {
			disable(1),
          enable(2)
		}
	MAX-ACCESS  read-write
	STATUS  current
	DESCRIPTION "Enable or disable Wireless client filtering
		"
	::= { apClientFiltering 3 }

apClientWiredFiltering OBJECT-TYPE
	SYNTAX  INTEGER {
			disable(1),
          enable(2)
		}
	MAX-ACCESS  read-write
	STATUS  current
	DESCRIPTION "Enable or disable Wireless client filtering
		"
	::= { apClientFiltering 4 }

apClientFilteringMACAddress OBJECT-TYPE
	SYNTAX  PhysAddress
	MAX-ACCESS  read-write
	STATUS  current
	DESCRIPTION "
		MAC address field
		"
	::= { apClientFiltering 5 }

apClientFilteringName OBJECT-TYPE
	SYNTAX OCTET STRING (SIZE (1..64))
  	MAX-ACCESS read-write
    STATUS current
    DESCRIPTION
            "Name Field
			"
  ::= { apClientFiltering 6}

apClientFilteringSave OBJECT-TYPE
	SYNTAX  INTEGER
	MAX-ACCESS  read-write
	STATUS  current
	DESCRIPTION "write 1 to save the rule
		"
	::= { apClientFiltering 7 }

apClientFilteringDelete OBJECT-TYPE
	SYNTAX  INTEGER
	MAX-ACCESS  read-write
	STATUS  current
	DESCRIPTION "when writed, delete the rule which is
			     indexed by the written value
		"
	::= { apClientFiltering 8 }

apClientFilteringEnableRule OBJECT-TYPE
	SYNTAX  INTEGER
	MAX-ACCESS  read-write
	STATUS  current
	DESCRIPTION "when writed, enable the rule which is
			     indexed by the written value
		"
	::= { apClientFiltering 9 }

apClientFilteringDisableRule OBJECT-TYPE
	SYNTAX  INTEGER
	MAX-ACCESS  read-write
	STATUS  current
	DESCRIPTION "when writed, disable the rule which is
			     indexed by the written value
		"
	::= { apClientFiltering 10 }

apClientFilteringTable OBJECT-TYPE
    SYNTAX  SEQUENCE OF ApClientFilteringEntry
    MAX-ACCESS  not-accessible
    STATUS  current
    DESCRIPTION
            "Significant only in MAX-ACCESS POINT mode. This table shows information AP bridge filtering rules list."
    ::= { apClientFiltering 11 }


apClientFilteringEntry OBJECT-TYPE
    SYNTAX  ApClientFilteringEntry
    MAX-ACCESS  not-accessible
    STATUS  current
   DESCRIPTION
            "Shows information of the rule.
	"
    INDEX   { apClientFilteringListId }
    ::= { apClientFilteringTable 1 }

ApClientFilteringEntry ::=
    SEQUENCE {
		apClientFilteringListId
			INTEGER,
      apClientFilteringListName
			OCTET STRING,
        apClientFilteringListMAC
            PhysAddress,
		apClientFilteringListEnable
			INTEGER
	}

apClientFilteringListId OBJECT-TYPE
    SYNTAX INTEGER
    MAX-ACCESS read-only
    STATUS current
    DESCRIPTION
            "Rule index."
    ::= { apClientFilteringEntry 1 }

apClientFilteringListMAC OBJECT-TYPE
    SYNTAX PhysAddress
    MAX-ACCESS read-only
    STATUS current
    DESCRIPTION
            "MAC address of the client."
    ::= { apClientFilteringEntry 3 }

apClientFilteringListName OBJECT-TYPE
    SYNTAX OCTET STRING (SIZE (1..64))
    MAX-ACCESS read-only
    STATUS current
    DESCRIPTION
            "Show rule's name"
    ::= { apClientFilteringEntry 2 }

apClientFilteringListEnable OBJECT-TYPE
	SYNTAX  INTEGER {
			disable(1),
            enable(2)
		}
	MAX-ACCESS  read-only
	STATUS  current
	DESCRIPTION "Show if the rule is enabled or not"
	::= { apClientFilteringEntry 4 }



--End AP Filtering
------------------------

------------------------
--WDS
apWDSEnable OBJECT-TYPE
	SYNTAX  INTEGER {
		disable(1),
        enable(2)
		}
	MAX-ACCESS  read-write
	STATUS  current
	DESCRIPTION "Enable or Disable WDS.
		"
	::= { wds 1 }

apWDSEnableSTP OBJECT-TYPE
	SYNTAX  INTEGER {
		disable(1),
        enable(2)
		}
	MAX-ACCESS  read-write
	STATUS  current
	DESCRIPTION "Enable or Disable STP when WDS is on

		"
	::= { wds 2 }

apWDSMAC1 OBJECT-TYPE
	SYNTAX  PhysAddress
	MAX-ACCESS  read-write
	STATUS  current
	DESCRIPTION "
		First AP mac address
		"
	::= { wds 3 }

apWDSMAC2 OBJECT-TYPE
	SYNTAX  PhysAddress
	MAX-ACCESS  read-write
	STATUS  current
	DESCRIPTION "
		Second AP mac address
		"
	::= { wds 4 }

apWDSMAC3 OBJECT-TYPE
	SYNTAX  PhysAddress
	MAX-ACCESS  read-write
	STATUS  current
	DESCRIPTION "
		Third AP mac address
		"
	::= { wds 5 }

apWDSMAC4 OBJECT-TYPE
	SYNTAX  PhysAddress
	MAX-ACCESS  read-write
	STATUS  current
	DESCRIPTION "
		fourth AP mac address
		"
	::= { wds 6 }

apWDSMAC5 OBJECT-TYPE
	SYNTAX  PhysAddress
	MAX-ACCESS  read-write
	STATUS  current
	DESCRIPTION "
		fith AP mac address
		"
	::= { wds 7 }

apWDSMAC6 OBJECT-TYPE
	SYNTAX  PhysAddress
	MAX-ACCESS  read-write
	STATUS  current
	DESCRIPTION "
		sixth AP mac address
		"
	::= { wds 8 }

--bridge group
bridge-modeLinkStatus OBJECT-TYPE
	SYNTAX  INTEGER {
			up(1),       -- ready to pass packets
            down(2)
		}
	MAX-ACCESS  read-only
	STATUS  current
	DESCRIPTION "MAX-ACCESS POINT's connection status.
		"
	::= { bridge-mode 1 }

bridge-modeMacAP OBJECT-TYPE
	SYNTAX  PhysAddress
	MAX-ACCESS  read-only
	STATUS  current
	DESCRIPTION "
		MAX-ACCESS POINT's MAC ADDRESS we are connected with.
	"
	::= { bridge-mode 2 }

bridge-modeRSSI OBJECT-TYPE
	SYNTAX  Gauge32
	MAX-ACCESS  read-only
	STATUS  current
	DESCRIPTION "
		MAX-ACCESS POINT's connection RSSI.
	 "
	::= { bridge-mode 3 }

bridge-modeRSSIdBm OBJECT-TYPE
	SYNTAX  Gauge32
	MAX-ACCESS  read-only
	STATUS  current
	DESCRIPTION "
		Connection's RSSI in dBm.
	"
	::= { bridge-mode 4 }

bridge-modeRSSIPercent OBJECT-TYPE
	SYNTAX  Gauge32
	MAX-ACCESS  read-only
	STATUS  current
	DESCRIPTION "
		Connection's RSSI in percent.
	"
	::= { bridge-mode 5}

bridge-modeCurrentTxRate OBJECT-TYPE
	SYNTAX  INTEGER
	MAX-ACCESS  read-only
	STATUS  current
	DESCRIPTION "
		Current communication speed in bits per second.
	"
	::= { bridge-mode 6}

bridge-WirelessMode OBJECT-TYPE
    SYNTAX INTEGER {
			infrastructure(1),
			ad-hoc(2)
		}
    MAX-ACCESS read-write
    STATUS current
    DESCRIPTION
    	" Select the Wireless mode. Infrastructure mode require an access point.
	"
    ::= { bridge-mode 7}

--*********************

--********************
-- bridge

bridgeAPFilteringEnable OBJECT-TYPE
	SYNTAX  INTEGER {
			off(1),
            on(2)
		}
	MAX-ACCESS  read-write
	STATUS  current
	DESCRIPTION "Enable or Disable AP Filtering.
		"
	::= { bridgeAPFiltering 1 }

bridgeAPFilteringMode OBJECT-TYPE
	SYNTAX  INTEGER {
			allow(1),
    	    deny(2)
		}
	MAX-ACCESS  read-write
	STATUS  current
	DESCRIPTION "Select AP Filtering Mode (allow/Deny)
		"
	::= { bridgeAPFiltering 2 }

bridgeAPFilteringMACAddress OBJECT-TYPE
	SYNTAX  PhysAddress
	MAX-ACCESS  read-write
	STATUS  current
	DESCRIPTION "
		MAC address field
		"
	::= { bridgeAPFiltering 3 }

bridgeAPFilteringName OBJECT-TYPE
	SYNTAX OCTET STRING (SIZE (1..64))
	MAX-ACCESS read-write
    STATUS current
    DESCRIPTION
            "Name Field
			"
    ::= { bridgeAPFiltering 4 }

bridgeAPFilteringSave OBJECT-TYPE
	SYNTAX  INTEGER
	MAX-ACCESS  read-write
	STATUS  current
	DESCRIPTION "write 1 to save the rule
		"
	::= { bridgeAPFiltering 5 }

bridgeAPFilteringDelete OBJECT-TYPE
	SYNTAX  INTEGER
	MAX-ACCESS  read-write
	STATUS  current
	DESCRIPTION "when writed, delete the rule which is
			     indexed by the written value
		"
	::= { bridgeAPFiltering 6 }

bridgeAPFilteringEnableRule OBJECT-TYPE
	SYNTAX  INTEGER
	MAX-ACCESS  read-write
	STATUS  current
	DESCRIPTION "when writed, enable the rule which is
			     indexed by the written value
		"
	::= { bridgeAPFiltering 7 }

bridgeAPFilteringDisableRule OBJECT-TYPE
	SYNTAX  INTEGER
	MAX-ACCESS  read-write
	STATUS  current
	DESCRIPTION "when writed, disable the rule which is
			     indexed by the written value
		"
	::= { bridgeAPFiltering 8 }


bridgeAPFilteringTable OBJECT-TYPE
    SYNTAX  SEQUENCE OF BridgeAPFilteringEntry
    MAX-ACCESS  not-accessible
    STATUS  current
    DESCRIPTION
            "Significant only in MAX-ACCESS POINT mode. This table shows information bridge AP filtering rules list."
    ::= { bridgeAPFiltering 9 }

bridgeAPFilteringEntry OBJECT-TYPE
    SYNTAX  BridgeAPFilteringEntry
    MAX-ACCESS  not-accessible
    STATUS  current
    DESCRIPTION
     "Shows information of the rule.
	"
    INDEX   { bridgeAPFilteringListId }
    ::= { bridgeAPFilteringTable 1 }

BridgeAPFilteringEntry ::=
    SEQUENCE {
		bridgeAPFilteringListId
			INTEGER,
	    bridgeAPFilteringListName
			OCTET STRING,
        bridgeAPFilteringListMAC
            PhysAddress,
		bridgeAPFilteringListEnable
			INTEGER
	}

bridgeAPFilteringListId OBJECT-TYPE
    SYNTAX INTEGER
    MAX-ACCESS read-only
    STATUS current
    DESCRIPTION
            "Rule index."
    ::= { bridgeAPFilteringEntry 1 }

bridgeAPFilteringListMAC OBJECT-TYPE
   SYNTAX PhysAddress
    MAX-ACCESS read-only
    STATUS current
    DESCRIPTION
            "MAC address of the client."
    ::= { bridgeAPFilteringEntry 3 }

bridgeAPFilteringListName OBJECT-TYPE
    SYNTAX OCTET STRING (SIZE (1..64))
    MAX-ACCESS read-only
    STATUS current
    DESCRIPTION
            "Show rule's name"
    ::= { bridgeAPFilteringEntry 2 }

bridgeAPFilteringListEnable OBJECT-TYPE
	SYNTAX  INTEGER {
	disable(1),
        enable(2)
		}
	MAX-ACCESS  read-only
	STATUS  current
	DESCRIPTION "Show if a rule is enabled or not.
				"
	::= { bridgeAPFilteringEntry 4 }

bridgeChannelList OBJECT-TYPE
	SYNTAX OCTET STRING (SIZE (1..40))
	MAX-ACCESS  read-write
	STATUS  current
	DESCRIPTION "A wireless network uses specific channels in the 2.4GHz or 5GHz wireless spectrum to handle communication between clients. Some channels in your area may have interference from other electronic devices. Your wireless bridge will use the channel that is used by the access point it will associate with. But you can select here your channel preference to help optimize the performance and coverage of your wireless network. If you used the roaming, Acksys recommend to used only one channel for better bandwith.
				"
	::= { bridge-mode 10 }

--roaming setting
bridgeRoamingEnable OBJECT-TYPE
	SYNTAX INTEGER{
	disable(1),
        enable(2)
		}
	MAX-ACCESS read-write
	STATUS  current
	DESCRIPTION " Roaming enables WiFi clients to roam among AP when WiFi RSSI of the current AP becomes weak. This radio button enables/disables the roaming capabilities of the bridge.
	"
	::={bridgeRoaming 2}

bridgeRoamingRSSIThreshold-dBm OBJECT-TYPE
	SYNTAX INTEGER
	MAX-ACCESS read-write
	STATUS  current
	DESCRIPTION " Allows to configure the RSSI roaming threshold (in dBm, or percent) from which the roaming algorithm (to find a better AP) will start. AP changing will only be effective if the current RSSI is lower than that threshold, and if a new AP with a better RSSI has been detected.
	"
	::= {bridgeRoaming 3}

bridgeRoamingRSSIThreshold-percent OBJECT-TYPE
	SYNTAX INTEGER
	MAX-ACCESS read-write
	STATUS  current
	DESCRIPTION " Allows to configure the RSSI roaming threshold (in dBm, or percent) from which the roaming algorithm (to find a better AP) will start. AP changing will only be effective if the current RSSI is lower than that threshold, and if a new AP with a better RSSI has been detected.
	"
	::= {bridgeRoaming 4}

bridgeRoamingAdvancedScanThreshold-dbm OBJECT-TYPE
	SYNTAX INTEGER
	MAX-ACCESS	read-write
	STATUS  current
	DESCRIPTION "Allows to configure the RSSI scan threshold (in dBm, or in percent) from which the access point active scan will start. The access point active scan process looking on each valid channel the access point where it will be possible to roam.
	"
	::= {bridgeRoamingAdvanced 1}

bridgeRoamingAdvancedScanThreshold-percent OBJECT-TYPE
	SYNTAX INTEGER
	MAX-ACCESS	read-write
	STATUS  current
	DESCRIPTION "Allows to configure the RSSI scan threshold (in dBm, or in percent) from which the access point active scan will start. The access point active scan process looking on each valid channel the access point where it will be possible to roam.
	"
	::= {bridgeRoamingAdvanced 2}

bridgeRoamingAdvancedScanPeriod OBJECT-TYPE
	SYNTAX INTEGER
	MAX-ACCESS	read-write
	STATUS  current
	DESCRIPTION "Allow to configure the time between two scan.
				Reduce this time increase the Access Point discover, but decrease the bandwith if you used more one channel.
	"
	::= {bridgeRoamingAdvanced 3}

bridgeRoamingAdvancedScanDuration OBJECT-TYPE
	SYNTAX INTEGER
	MAX-ACCESS	read-write
	STATUS  current
	DESCRIPTION "Allow to configure the duration while the bridge waiting the Access Point answer.
					Reduce this duration increase the Bandwith when you used more one channel, but decrase the Access Point discover.
	"
	::= {bridgeRoamingAdvanced 4}

bridgeRoamingAdvancedAPLossDetection OBJECT-TYPE
	SYNTAX INTEGER
	MAX-ACCESS	read-write
	STATUS  current
	DESCRIPTION "If nothing is received from the AP during a certain amount of time, it will be considered unreachable.
				This amount of time is computed as:
			   	 'AP timeout' = 'AP loss detection' x 'beacon interval'.
				The recommended value for 'AP loss detection' is 5.
				The recommended value for 'Beacon interval' (which should be configured in your AP) is 50 ms.
				If the AP timeout is set too low, it may decrease the bandwidth and roaming performance.

	"
	::= {bridgeRoamingAdvanced 5}

-- End bridge filter
--***********************

--Bridge status scan
bridgeWileressScanTable OBJECT-TYPE
    SYNTAX  SEQUENCE OF BridgeWirelessScanEntry
    MAX-ACCESS  not-accessible
    STATUS  current
    DESCRIPTION
            "Significant only in MAX-ACCESS POINT mode. This table shows information AP bridge filtering rules list."
    ::= { bridgeWirelessScan 1 }


bridgeWirelessScanEntry OBJECT-TYPE
    SYNTAX  BridgeWirelessScanEntry
    MAX-ACCESS  not-accessible
    STATUS  current
   DESCRIPTION
            "Shows information of the rule.
	"
    INDEX   { apClientFilteringListId }
    ::= { bridgeWileressScanTable 1 }

BridgeWirelessScanEntry ::=
	SEQUENCE {
		bridgeWirelessScanAPMac
			PhysAddress,
		bridgeWirelessScanSSID
			DisplayString,
		bridgeWirelessScanChannel
			INTEGER,
		bridgeWirelessScanMode
			INTEGER,
		bridgeWirelessScanSecurity
			INTEGER,
		bridgeWirelessScanRssi
			INTEGER
	}

bridgeWirelessScanAPMac OBJECT-TYPE
    SYNTAX PhysAddress
    MAX-ACCESS read-only
    STATUS current
    DESCRIPTION
            "MAC address of the access point."
    ::= { bridgeWirelessScanEntry 1 }

bridgeWirelessScanSSID OBJECT-TYPE
    SYNTAX DisplayString (SIZE (0..33))
    MAX-ACCESS read-only
    STATUS current
    DESCRIPTION
            ""
    ::= { bridgeWirelessScanEntry 2 }

bridgeWirelessScanChannel OBJECT-TYPE
    SYNTAX INTEGER
    MAX-ACCESS read-only
    STATUS current
    DESCRIPTION
            ""
    ::= { bridgeWirelessScanEntry 3 }


bridgeWirelessScanMode OBJECT-TYPE
    SYNTAX INTEGER {
		b-only(1),
		g-only(2),
		mixed-b-g(3),
		a-only(4)
    }
    MAX-ACCESS read-only
    STATUS current
    DESCRIPTION
            "Show AP's IEEE 802.11x compatibility mode."
    ::= { bridgeWirelessScanEntry 4 }

bridgeWirelessScanSecurity OBJECT-TYPE
    SYNTAX INTEGER {
    		none(0),
			wep(1),
			wpa(2)
		}
    MAX-ACCESS read-only
    STATUS current
    DESCRIPTION
            ""
    ::= { bridgeWirelessScanEntry 5 }

bridgeWirelessScanRssi OBJECT-TYPE
    SYNTAX INTEGER
    MAX-ACCESS read-only
    STATUS current
    DESCRIPTION
            ""
    ::= { bridgeWirelessScanEntry 6 }



--end bridge status scan

--BrigeNAT
brigeNATStatus OBJECT-TYPE
    SYNTAX INTEGER {
    		disable(1),
			enable(2)
		}
    MAX-ACCESS read-write
    STATUS current
    DESCRIPTION
            "Enable / disable NAT
"
    ::= { bridgeNAT 1 }

brigeNATEnablePing OBJECT-TYPE
    SYNTAX INTEGER {
    		disable(1),
			enable(2)
		}
    MAX-ACCESS read-write
    STATUS current
    DESCRIPTION
            "Enable / disable ping response from WAN
			"
    ::= { bridgeNAT 2 }

brigeNATEnableProductWebServer OBJECT-TYPE
    SYNTAX INTEGER {
    		disable(1),
			enable(2)
		}
    MAX-ACCESS read-write
    STATUS current
    DESCRIPTION
            "Enable / disable the internal web server from WAN
			"
    ::= { bridgeNAT 3 }

brigeNATInternalWebServerPort OBJECT-TYPE
    SYNTAX INTEGER
    MAX-ACCESS read-write
    STATUS current
    DESCRIPTION
            "TCP port used by internal web server from WAN
			"
    ::= { bridgeNAT 4 }

brigeNATEnableProductSnmpServer OBJECT-TYPE
    SYNTAX INTEGER {
    		disable(1),
		enable(2)
		}
    MAX-ACCESS read-write
    STATUS current
    DESCRIPTION
            "Enable / disable the internal snmp server from WAN
			"
    ::= { bridgeNAT 5 }

brigeNATInternalWebSnmpPort OBJECT-TYPE
    SYNTAX INTEGER
    MAX-ACCESS read-write
    STATUS current
    DESCRIPTION
            "TCP port used by internal snmp server from WAN
			"
    ::= { bridgeNAT 6 }


brigeNATWanIpAddrMode OBJECT-TYPE
    SYNTAX  INTEGER {static(1),dhcp(2)}
    MAX-ACCESS read-write
    STATUS current
    DESCRIPTION
            "Ip address mode on wan side
			"
    ::= { bridgeNAT 7 }

brigeNATWanIpAddr OBJECT-TYPE
    SYNTAX  IpAddress
    MAX-ACCESS read-write
    STATUS current
    DESCRIPTION
            "Static Ip address on wan side
			"
    ::= { bridgeNAT 8 }

brigeNATWanSubnetMask OBJECT-TYPE
    SYNTAX  IpAddress
    MAX-ACCESS read-write
    STATUS current
    DESCRIPTION
            "Subnet mask on wan side
			"
    ::= { bridgeNAT 9 }

brigeNATWanGateway OBJECT-TYPE
    SYNTAX  IpAddress
    MAX-ACCESS read-write
    STATUS current
    DESCRIPTION
            "Gateway ip address on wan side
			"
    ::= { bridgeNAT 10 }

	bridgeNatPortForwardingName OBJECT-TYPE
    SYNTAX  OCTET STRING (SIZE (0..20))
    MAX-ACCESS  read-write
    STATUS current
    DESCRIPTION
            "Show rule's name
			"
    ::= { bridgeNatPortForwarding 2 }

	bridgeNatPortForwardingIpAddr OBJECT-TYPE
    SYNTAX  IpAddress
    MAX-ACCESS read-write
    STATUS current
    DESCRIPTION
            "Show ipaddress to forward data
			"
    ::= { bridgeNatPortForwarding 3 }

	bridgeNatPortForwardingPublicTcpPort OBJECT-TYPE
    SYNTAX   OCTET STRING (SIZE (0..20))
    MAX-ACCESS  read-write
    STATUS current
    DESCRIPTION
            "Show public TCP port
			"
    ::= { bridgeNatPortForwarding 4 }

	bridgeNatPortForwardingPrivateTcpPort OBJECT-TYPE
    SYNTAX   OCTET STRING (SIZE (0..20))
    MAX-ACCESS  read-write
    STATUS current
    DESCRIPTION
            "Show private TCP port
			"
    ::= { bridgeNatPortForwarding 5 }

	bridgeNatPortForwardingPublicUdpPort OBJECT-TYPE
    SYNTAX   OCTET STRING (SIZE (0..20))
    MAX-ACCESS  read-write
    STATUS current
    DESCRIPTION
            "Show public TCP port
			"
    ::= { bridgeNatPortForwarding 6 }

	bridgeNatPortForwardingPrivateUdpPort OBJECT-TYPE
    SYNTAX   OCTET STRING (SIZE (0..20))
    MAX-ACCESS  read-write
    STATUS current
    DESCRIPTION
            "Show private TCP port
			"
    ::= { bridgeNatPortForwarding 7 }

bridgeNatPortForwardingEnableRule OBJECT-TYPE
    SYNTAX  INTEGER
    MAX-ACCESS  read-write
    STATUS current
    DESCRIPTION
            "when writed, enable the rule which is
			     indexed by the written value
		"
    ::= { bridgeNatPortForwarding 8 }

bridgeNatPortForwardingDisableRule OBJECT-TYPE
    SYNTAX  INTEGER
    MAX-ACCESS  read-write
    STATUS current
    DESCRIPTION
            "when writed, disable the rule which is
			     indexed by the written value
		"
    ::= { bridgeNatPortForwarding 9 }

bridgeNatPortForwardingSaveRule OBJECT-TYPE
    SYNTAX  INTEGER
    MAX-ACCESS  read-write
    STATUS current
    DESCRIPTION
            "when writed, save the rule which is
			     indexed by the written value
		"
    ::= { bridgeNatPortForwarding 10 }

bridgeNatPortForwardingDeleteRule OBJECT-TYPE
    SYNTAX  INTEGER
    MAX-ACCESS read-write
    STATUS current
    DESCRIPTION
            "when writed, delete the rule which is
			     indexed by the written value
		"
    ::= { bridgeNatPortForwarding 11 }

bridgeNatPortForwardingTable OBJECT-TYPE
	SYNTAX SEQUENCE OF BridgeNatPortForwardingEntry
	MAX-ACCESS not-accessible
	STATUS current
	DESCRIPTION
	"
	This table show information on port forwading rules
	"
	::= { bridgeNatPortForwarding 1 }

bridgeNatPortForwardingEntry OBJECT-TYPE
	SYNTAX BridgeNatPortForwardingEntry
	MAX-ACCESS not-accessible
	STATUS current
	DESCRIPTION
		"shows information of rule.
		"
		INDEX {bridgeNatPortForwardingListId}
	::= {bridgeNatPortForwardingTable 1}

BridgeNatPortForwardingEntry ::=
	SEQUENCE {
		bridgeNatPortForwardingListId
			INTEGER,
		bridgeNatPortForwardingListEnable
			INTEGER,
		bridgeNatPortForwardingListName
			OCTET STRING,
		bridgeNatPortForwardingListIpAddr
			IpAddress,
		bridgeNatPortForwardingListPublicTcpPort
			OCTET STRING,
		bridgeNatPortForwardingListPrivateTcpPort
			OCTET STRING,
		bridgeNatPortForwardingListPublicUdpPort
			OCTET STRING,
		bridgeNatPortForwardingListPrivateUdpPort
			OCTET STRING
	}

	bridgeNatPortForwardingListId OBJECT-TYPE
    SYNTAX  INTEGER
    MAX-ACCESS read-only
    STATUS current
    DESCRIPTION
            "Rule index"
    ::= { bridgeNatPortForwardingEntry 1 }

	bridgeNatPortForwardingListName OBJECT-TYPE
    SYNTAX  OCTET STRING (SIZE (0..20))
    MAX-ACCESS read-only
    STATUS current
    DESCRIPTION
            "Show rule's name"
    ::= { bridgeNatPortForwardingEntry 2 }

	bridgeNatPortForwardingListIpAddr OBJECT-TYPE
    SYNTAX  IpAddress
    MAX-ACCESS read-only
    STATUS current
    DESCRIPTION
            "Show ipaddress to forward data"
    ::= { bridgeNatPortForwardingEntry 3 }

	bridgeNatPortForwardingListPublicTcpPort OBJECT-TYPE
    SYNTAX   OCTET STRING (SIZE (0..20))
    MAX-ACCESS read-only
    STATUS current
    DESCRIPTION
            "Show public TCP port"
    ::= { bridgeNatPortForwardingEntry 4 }

	bridgeNatPortForwardingListPrivateTcpPort OBJECT-TYPE
    SYNTAX   OCTET STRING (SIZE (0..20))
    MAX-ACCESS read-only
    STATUS current
    DESCRIPTION
            "Show private TCP port"
    ::= { bridgeNatPortForwardingEntry 5 }

	bridgeNatPortForwardingListPublicUdpPort OBJECT-TYPE
    SYNTAX   OCTET STRING (SIZE (0..20))
    MAX-ACCESS read-only
    STATUS current
    DESCRIPTION
            "Show public TCP port"
    ::= { bridgeNatPortForwardingEntry 6 }

	bridgeNatPortForwardingListPrivateUdpPort OBJECT-TYPE
    SYNTAX   OCTET STRING (SIZE (0..20))
    MAX-ACCESS read-only
    STATUS current
    DESCRIPTION
            "Show private TCP port"
    ::= { bridgeNatPortForwardingEntry 7 }

	bridgeNatPortForwardingListEnable OBJECT-TYPE
    SYNTAX  INTEGER {
		disable(1),
		enable(2)}
    MAX-ACCESS read-only
    STATUS current
    DESCRIPTION
            "Rule state"
    ::= { bridgeNatPortForwardingEntry 8 }

--end bridgeNAT
--*********************

-- Administration group

adminReset OBJECT-TYPE
	SYNTAX  INTEGER {reset(1)}
	MAX-ACCESS  read-write
	STATUS  current
	DESCRIPTION "
		Writing 1 resets the product. This must be done after each configuration change.
	"
	::= { administration 1}

adminResetFactory OBJECT-TYPE
	SYNTAX  INTEGER {resetfactory(1)}
	MAX-ACCESS  read-write
	STATUS  current
	DESCRIPTION "
		Writing 1 resets the product to the factory settings.
	"
	::= { administration 2}

adminEnableWebServer OBJECT-TYPE
    SYNTAX INTEGER {
			disable(1),
			enable(2)
		}
    MAX-ACCESS read-write
    STATUS current
    DESCRIPTION
    	" Enable or Disable internal webserver.
	"
    ::= { administration 3}

adminAutoSave OBJECT-TYPE
    SYNTAX INTEGER {
			disable(1),
			enable(2)
		}
    MAX-ACCESS read-write
    STATUS current
    DESCRIPTION
    	" Enable or Disable the automatic change saving. When this function is disable, the modification is not save automaticaly after change and certainly OID is applied imediatly.

	"
    ::= { administration 4}

adminSave OBJECT-TYPE
    SYNTAX INTEGER {
			saveNotRequire(3),
			saveRequire(2)
		}
    MAX-ACCESS read-write
    STATUS current
    DESCRIPTION
    	" Write 1 to save the modification in flash. Read this OID to know if a save is require.
	"
    ::= { administration 5}


-- os-stat  group
os-statFreeHeap OBJECT-TYPE
    SYNTAX INTEGER
    MAX-ACCESS read-only
    STATUS current
    DESCRIPTION
            "The amount of memory currently available, measured in bytes.
		"
    ::= { os-stat  1 }

os-statTotalHeap OBJECT-TYPE
    SYNTAX INTEGER
    MAX-ACCESS read-only
    STATUS current
    DESCRIPTION
            "The total size of the heap, measured in bytes.
		"
    ::= { os-stat  2 }

os-statHeapLowWater OBJECT-TYPE
    SYNTAX INTEGER
    MAX-ACCESS read-only
    STATUS current
    DESCRIPTION
            "Low water mark for the heap. Writing any value this variable will always
	    reset the low water to the total heap size.
	    "
    ::= { os-stat  3 }

os-statNetpageFree OBJECT-TYPE
    SYNTAX INTEGER
    MAX-ACCESS read-only
    STATUS current
    DESCRIPTION
            "The amount of netpages currently available, measured in bytes.
	    "
    ::= { os-stat  4 }

os-statNetpageLowWater OBJECT-TYPE
    SYNTAX INTEGER
    MAX-ACCESS read-only
    STATUS current
    DESCRIPTION
            "Low water mark for the netpage.
	    "
    ::= { os-stat  5 }


-- wlg-aboard group
wlg-aboard-PW1-state OBJECT-TYPE
    SYNTAX INTEGER {powerOff(1), powerOn(2)}
    MAX-ACCESS read-only
    STATUS obsolete
    DESCRIPTION
	    "Power 1 state
	    "
    ::= { wlg-aboard  1 }

wlg-aboard-PW2-state OBJECT-TYPE
    SYNTAX INTEGER {powerOff(1), powerOn(2)}
    MAX-ACCESS read-only
    STATUS obsolete
    DESCRIPTION
	    "Power 2 state
	    "
    ::= { wlg-aboard  2 }

-- lanInterface group
lanInterfaceIpAddrMode OBJECT-TYPE
    SYNTAX  INTEGER {static(1),dhcp(2)}
    MAX-ACCESS  read-write
    STATUS  current
    DESCRIPTION
            "Static or DHCP Ip settings
		"

    ::= { lanInterface 1 }

lanInterfaceIpAddr OBJECT-TYPE
    SYNTAX  IpAddress
    MAX-ACCESS  read-write
    STATUS  current
    DESCRIPTION
            "Product IP address
		"
    ::= { lanInterface 2 }

lanInterfaceSubNetMask OBJECT-TYPE
    SYNTAX  IpAddress
    MAX-ACCESS  read-write
    STATUS  current
    DESCRIPTION
            "Network mask
		"
    ::= { lanInterface 3 }

lanInterfaceGatewayIp OBJECT-TYPE
    SYNTAX  IpAddress
    MAX-ACCESS  read-write
    STATUS  current
    DESCRIPTION
            "IP gateway
		"
    ::= { lanInterface 4 }

lanInterfaceHostName OBJECT-TYPE
    SYNTAX  OCTET STRING (SIZE (1..64))
    MAX-ACCESS  read-write
    STATUS  current
    DESCRIPTION
            "Adresse IP de la gateway
		"
    ::= { lanInterface 5 }

lanInterfaceLocalDomainName OBJECT-TYPE
    SYNTAX  OCTET STRING (SIZE (1..33))
    MAX-ACCESS  read-write
    STATUS  current
    DESCRIPTION
            "Adresse IP de la gateway
		"
    ::= { lanInterface 6 }

-- c-key-management
ckeyManagementCopySettingTo OBJECT-TYPE
    SYNTAX  INTEGER
    MAX-ACCESS  read-write
    STATUS  current
    DESCRIPTION
            "
		Write 1 to copy the current settings to the C-KEY. After this action, all previous data in the C-KEY are lost.

"
    ::= { c-key-management 1 }

ckeyManagementCopySettingFrom OBJECT-TYPE
    SYNTAX  INTEGER
    MAX-ACCESS  read-write
    STATUS  current
    DESCRIPTION
	      "
		Write 1 to copy the product settings from the C-KEY. After this action, the product has C-KEY settings. Reboot your device to apply the new settings.

"
    ::= { c-key-management 2 }

-- alarmSettings
alarmSettingsTest OBJECT-TYPE
    SYNTAX  INTEGER {set(1),clear(2)}
    MAX-ACCESS  read-write
    STATUS  current
    DESCRIPTION
	      "
		Allow to get and set the Alarm output status.

"
    ::= { alarmSettings 1 }

alarmSettingsPower1DownEnable OBJECT-TYPE
    SYNTAX  INTEGER {disable(1),enable(2)}
    MAX-ACCESS  read-write
    STATUS  current
    DESCRIPTION
	      "
"
    ::= { alarmSettingsPower1Down 1 }

alarmSettingsPower1DownEnableAutomaticReset OBJECT-TYPE
    SYNTAX  INTEGER {disable(1),enable(2)}
    MAX-ACCESS  read-write
    STATUS  current
    DESCRIPTION
	      "
"
    ::= { alarmSettingsPower1Down 2 }

alarmSettingsPower1DownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsPower1Down 3 }

alarmSettingsPower2DownEnable OBJECT-TYPE
    SYNTAX  INTEGER {disable(1),enable(2)}
    MAX-ACCESS  read-write
    STATUS  current
    DESCRIPTION
	      "
"
    ::= { alarmSettingsPower2Down 1 }

alarmSettingsPower2DownEnableAutomaticReset OBJECT-TYPE
    SYNTAX  INTEGER {disable(1),enable(2)}
    MAX-ACCESS  read-write
    STATUS  current
    DESCRIPTION
	      "
"
    ::= { alarmSettingsPower2Down 2 }

alarmSettingsPower2DownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsPower2Down 3 }

alarmSettingsLan1DownEnable OBJECT-TYPE
    SYNTAX  INTEGER {disable(1),enable(2)}
    MAX-ACCESS  read-write
    STATUS  current
    DESCRIPTION
	      "
"
    ::= { alarmSettingsLan1Down 1 }

alarmSettingsLan1DownEnableAutomaticReset OBJECT-TYPE
    SYNTAX  INTEGER {disable(1),enable(2)}
    MAX-ACCESS  read-write
    STATUS  current
    DESCRIPTION
	      "
"
    ::= { alarmSettingsLan1Down 2 }

alarmSettingsLan1DownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsLan1Down 3 }

alarmSettingsLan2DownEnable OBJECT-TYPE
    SYNTAX  INTEGER {disable(1),enable(2)}
    MAX-ACCESS  read-write
    STATUS  current
    DESCRIPTION
	      "
"
    ::= { alarmSettingsLan2Down 1 }

alarmSettingsLan2DownEnableAutomaticReset OBJECT-TYPE
    SYNTAX  INTEGER {disable(1),enable(2)}
    MAX-ACCESS  read-write
    STATUS  current
    DESCRIPTION
	      "
"
    ::= { alarmSettingsLan2Down 2 }

alarmSettingsLan2DownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsLan2Down 3 }

alarmSettingsLan3DownEnable OBJECT-TYPE
    SYNTAX  INTEGER {disable(1),enable(2)}
    MAX-ACCESS  read-write
    STATUS  current
    DESCRIPTION
	      "
"
    ::= { alarmSettingsLan3Down 1 }

alarmSettingsLan3DownEnableAutomaticReset OBJECT-TYPE
    SYNTAX  INTEGER {disable(1),enable(2)}
    MAX-ACCESS  read-write
    STATUS  current
    DESCRIPTION
	      "
"
    ::= { alarmSettingsLan3Down 2 }

alarmSettingsLan3DownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsLan3Down 3 }

alarmSettingsLan4DownEnable OBJECT-TYPE
    SYNTAX  INTEGER {disable(1),enable(2)}
    MAX-ACCESS  read-write
    STATUS  current
    DESCRIPTION
	      "
"
    ::= { alarmSettingsLan4Down 1 }

alarmSettingsLan4DownEnableAutomaticReset OBJECT-TYPE
    SYNTAX  INTEGER {disable(1),enable(2)}
    MAX-ACCESS  read-write
    STATUS  current
    DESCRIPTION
	      "
"
    ::= { alarmSettingsLan4Down 2 }

alarmSettingsLan4DownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsLan4Down 3 }

alarmSettingsLan5DownEnable OBJECT-TYPE
    SYNTAX  INTEGER {disable(1),enable(2)}
    MAX-ACCESS  read-write
    STATUS  current
    DESCRIPTION
	      "
"
    ::= { alarmSettingsLan5Down 1 }

alarmSettingsLan5DownEnableAutomaticReset OBJECT-TYPE
    SYNTAX  INTEGER {disable(1),enable(2)}
    MAX-ACCESS  read-write
    STATUS  current
    DESCRIPTION
	      "
"
    ::= { alarmSettingsLan5Down 2 }

alarmSettingsLan5DownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsLan5Down 3 }

alarmSettingsLan6DownEnable OBJECT-TYPE
    SYNTAX  INTEGER {disable(1),enable(2)}
    MAX-ACCESS  read-write
    STATUS  current
    DESCRIPTION
	      "
"
    ::= { alarmSettingsLan6Down 1 }

alarmSettingsLan6DownEnableAutomaticReset OBJECT-TYPE
    SYNTAX  INTEGER {disable(1),enable(2)}
    MAX-ACCESS  read-write
    STATUS  current
    DESCRIPTION
	      "
"
    ::= { alarmSettingsLan6Down 2 }

alarmSettingsLan6DownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsLan6Down 3 }

alarmSettingsLan7DownEnable OBJECT-TYPE
    SYNTAX  INTEGER {disable(1),enable(2)}
    MAX-ACCESS  read-write
    STATUS  current
    DESCRIPTION
	      "
"
    ::= { alarmSettingsLan7Down 1 }

alarmSettingsLan7DownEnableAutomaticReset OBJECT-TYPE
    SYNTAX  INTEGER {disable(1),enable(2)}
    MAX-ACCESS  read-write
    STATUS  current
    DESCRIPTION
	      "
"
    ::= { alarmSettingsLan7Down 2 }

alarmSettingsLan7DownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsLan7Down 3}

alarmSettingsLan8DownEnable OBJECT-TYPE
    SYNTAX  INTEGER {disable(1),enable(2)}
    MAX-ACCESS  read-write
    STATUS  current
    DESCRIPTION
	      "
"
    ::= { alarmSettingsLan8Down 1 }

alarmSettingsLan8DownEnableAutomaticReset OBJECT-TYPE
    SYNTAX  INTEGER {disable(1),enable(2)}
    MAX-ACCESS  read-write
    STATUS  current
    DESCRIPTION
	      "
"
    ::= { alarmSettingsLan8Down 2 }

alarmSettingsLan8DownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsLan8Down 3 }

alarmSettingsWLANDownEnable OBJECT-TYPE
    SYNTAX  INTEGER {disable(1),enable(2)}
    MAX-ACCESS  read-write
    STATUS  current
    DESCRIPTION
	      "
"
    ::= { alarmSettingsWLANDown 1 }

alarmSettingsWLANDownEnableAutomaticReset OBJECT-TYPE
    SYNTAX  INTEGER {disable(1),enable(2)}
    MAX-ACCESS  read-write
    STATUS  current
    DESCRIPTION
	      "
"
    ::= { alarmSettingsWLANDown 2 }

alarmSettingsWLANDownStatus OBJECT-TYPE
    SYNTAX  INTEGER {disable(1),enable(2),ack(3)}
    MAX-ACCESS  read-write
    STATUS  current
    DESCRIPTION
	      "
			Read to know the alarm source status (disable / enable )
			Write 3 to acknowledge the alarm source.

"
    ::= { alarmSettingsWLANDown 3 }

-- powerStatus
powerStatus-PW1-state OBJECT-TYPE
    SYNTAX INTEGER {powerOff(1), powerOn(2)}
    MAX-ACCESS read-only
    STATUS current
    DESCRIPTION
	    "Power 1 state
	    "
    ::= { powerStatus  1 }

powerStatus-PW2-state OBJECT-TYPE
    SYNTAX INTEGER {powerOff(1), powerOn(2)}
    MAX-ACCESS read-only
    STATUS current
    DESCRIPTION
	    "Power 2 state
	    "
    ::= { powerStatus  2 }
--***********************
-- Serial interface

-- ------------------------
-- +++ Serial format +++

END
