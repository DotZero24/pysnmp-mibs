HM2-QOS-MIB DEFINITIONS ::= BEGIN

--
-- *************************************************************
-- Hirschmann Quality of Service MIB
-- *************************************************************
--

IMPORTS
    MODULE-IDENTITY 			FROM SNMPv2-SMI -- RFC 2578
    hm2ConfigurationMibs        FROM HM2-TC-MIB;

hm2QosMib MODULE-IDENTITY
	LAST-UPDATED "201103160000Z" -- March 16, 2011
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Hirschmann Quality of Service MIB.
         Copyright (C) 2011. All Rights Reserved."
    REVISION     "201103160000Z" -- March 16, 2011
    DESCRIPTION
         "Initial version."
    ::= { hm2ConfigurationMibs 32 }

--
-- *************************************************************
-- hm2QosMib
-- *************************************************************
--
hm2QosMibNotifications		OBJECT IDENTIFIER ::= { hm2QosMib 0 }
hm2QosMibObjects			OBJECT IDENTIFIER ::= { hm2QosMib 1 }
-- hm2QosMibConformance			OBJECT IDENTIFIER ::= { hm2QosMib 2 }

--
-- *************************************************************
-- hm2QosMib groups
-- *************************************************************
--
hm2QosFirstGroup 	OBJECT IDENTIFIER ::= { hm2QosMibObjects 1 }
hm2QosNextGroup 	OBJECT IDENTIFIER ::= { hm2QosMibObjects 2 }


END
