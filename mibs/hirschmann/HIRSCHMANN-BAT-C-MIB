HIRSCHMANN-BAT-C-MIB DEFINITIONS ::= BEGIN

--
-- The hirschmann private EPA SNMP MIB:
--


IMPORTS

	MODULE-IDENTITY,
	OBJECT-TYPE,
	NOTIFICATION-TYPE,
	Integer32,
	IpAddress,
	enterprises
		FROM SNMPv2-SMI
	DisplayString,
	MacAddress,
	TEXTUAL-CONVENTION
		FROM SNMPv2-TC;

hmModuleIdentity MODULE-IDENTITY
	LAST-UPDATED	"201205090000Z"
	ORGANIZATION	"Hirschmann"
	CONTACT-INFO	"Hirschmann Automation and Control GmbH"
	DESCRIPTION		"Hirschmann BAT-C"
	REVISION		"201205090000Z"
	DESCRIPTION		"First revision"
::= { hirschmann 6 }

hirschmann
	OBJECT IDENTIFIER ::= { enterprises 248 }

EnabledDisabledStatus ::= TEXTUAL-CONVENTION
    STATUS current
    DESCRIPTION
        "This textual convention is used to some variables on the
        device that only permit two states.
        enableStatus  : The status of the variable is enabled or true.
        disableStatus : The status of the variable is disabled or false"
    SYNTAX INTEGER {
        disableStatus(0),
        enableStatus(1)
    }
--
--
--
--
-- The hirschmann private SNMP MIB objects level 1:
--
--



    hmComponents
        OBJECT IDENTIFIER ::= { hirschmann 1 }

    hmFirmware
        OBJECT IDENTIFIER ::= { hirschmann 2 }

    hmNet
        OBJECT IDENTIFIER ::= { hirschmann 3 }

    hmWLAN
        OBJECT IDENTIFIER ::= { hirschmann 5 }


--
--
--
--
-- The hirschmann private SNMP MIB objects level 2:
--
--
	hmWLANParameter
		OBJECT IDENTIFIER ::= { hmWLAN 1 }

	hmWLANSecurity
		OBJECT IDENTIFIER ::= { hmWLAN 2 }


--
--
--
--
-- The hirschmann private SNMP MIB objects level 3:
--
--
	--
	--
    -- hmComponents Group
    --
    hmComponentsTable
        OBJECT-TYPE
            SYNTAX      SEQUENCE OF HmComponentsEntry
            MAX-ACCESS  not-accessible
            STATUS      current
            DESCRIPTION
                "Table of descriptive information about the available
                 components of the product group."
        ::= { hmComponents 1 }

    hmComponentsEntry
        OBJECT-TYPE
            SYNTAX      HmComponentsEntry
            MAX-ACCESS  not-accessible
            STATUS      current
            DESCRIPTION
                "An entry in the table, containing information about a
                 single component (product)."
            INDEX       { hmComponentsIndex }
        ::= { hmComponentsTable 1 }

    HmComponentsEntry
        ::= SEQUENCE {
            hmComponentsIndex
                Integer32,
            hmComponentsName
                DisplayString,
            hmComponentsDescr
                DisplayString,
            hmComponentsURL
                DisplayString,
            hmComponentsOrderNumber
                DisplayString
        }

    hmComponentsIndex
        OBJECT-TYPE
            SYNTAX      Integer32 (1..1024)
            MAX-ACCESS  read-only
            STATUS      current
            DESCRIPTION
                "This object identifies the component for
				which this entry contains information."
        ::= { hmComponentsEntry 1 }

    hmComponentsName
        OBJECT-TYPE
            SYNTAX      DisplayString
            MAX-ACCESS  read-only
            STATUS      current
            DESCRIPTION
                "This object contains the component name."
        ::= { hmComponentsEntry 2 }

    hmComponentsDescr
        OBJECT-TYPE
            SYNTAX      DisplayString
            MAX-ACCESS  read-only
            STATUS      current
            DESCRIPTION
                "This object contains the component description."
        ::= { hmComponentsEntry 3 }

    hmComponentsURL
        OBJECT-TYPE
            SYNTAX      DisplayString
            MAX-ACCESS  read-only
            STATUS      current
            DESCRIPTION
                "This object contains the URL of component's web page."
        ::= { hmComponentsEntry 4 }

    hmComponentsOrderNumber
        OBJECT-TYPE
            SYNTAX      DisplayString
            MAX-ACCESS  read-only
            STATUS      current
            DESCRIPTION
                "This object contains the component order number."
        ::= { hmComponentsEntry 5 }


    --
    -- hmFirmware Group
    --
    hmFirmwareVersion
        OBJECT-TYPE
            SYNTAX      DisplayString
            MAX-ACCESS  read-only
            STATUS      current
            DESCRIPTION
                "This object represents the version string
                 of the firmware release."
        ::= { hmFirmware 1 }

    hmFirmwareState
        OBJECT-TYPE
            SYNTAX      DisplayString
            MAX-ACCESS  read-only
            STATUS      current
            DESCRIPTION
                "This object represent the current status
                 string of the firmware release."
        ::= { hmFirmware 2 }

    hmFirmwareDate
        OBJECT-TYPE
            SYNTAX      DisplayString
            MAX-ACCESS  read-only
            STATUS      current
            DESCRIPTION
                "This object represent the compiling date
                 string of the firmware release."
        ::= { hmFirmware 3 }

    hmFirmwareTime
        OBJECT-TYPE
            SYNTAX      DisplayString
            MAX-ACCESS  read-only
            STATUS      current
            DESCRIPTION
                "This object represent the compiling time
                 string of the firmware release."
        ::= { hmFirmware 4 }

    hmFirmwareCopyright
        OBJECT-TYPE
            SYNTAX      DisplayString
            MAX-ACCESS  read-only
            STATUS      current
            DESCRIPTION
                "This object represent the current copyright
                 string of the firmware release like next:

                    2008 Copyright by hirschmann AB"
        ::= { hmFirmware 5 }

    --
    --
    -- hmNet Group
    --
    hmNetPhyAddress
        OBJECT-TYPE
            SYNTAX      MacAddress
            MAX-ACCESS  read-only
            STATUS      current
            DESCRIPTION
               "The Ethernet MAC address of the device."
        ::= { hmNet 1 }

    hmNetIpAddress
        OBJECT-TYPE
            SYNTAX      IpAddress
            MAX-ACCESS  read-write
            STATUS      current
            DESCRIPTION
               "The ip address of this device. Changing this
			   object will not take effect until after a reset."
			DEFVAL  { 'c0a80063'h }  -- 192.168.0.99
        ::= { hmNet 2 }

    hmNetSubnetmask
        OBJECT-TYPE
            SYNTAX      IpAddress
            MAX-ACCESS  read-write
            STATUS      current
            DESCRIPTION
               "The subnet mask associated with the IP address of
                this entry.  The value of the mask is an IP
                address with all the network bits set to 1 and all
                the hosts bits set to 0. Changing this object will
				not take effect until after a reset."
			DEFVAL  { 'ffff0000'h }  -- 255.255.0.0
        ::= { hmNet 3 }

    hmNetGwIpAddress
        OBJECT-TYPE
            SYNTAX      IpAddress
            MAX-ACCESS  read-write
            STATUS      current
            DESCRIPTION
               "IP address of the default gateway. Changing this
			   object will not take effect until after a reset."
            DEFVAL  { '00000000'h }  -- 0.0.0.0
        ::= { hmNet 4 }


    hmNetAssignment
        OBJECT-TYPE
            SYNTAX      INTEGER {
                            other(0),
                            static(1),
                            dhcp(3)
						}
            MAX-ACCESS  read-write
            STATUS      current
            DESCRIPTION
                "Kind of the IP address assignment. Changing this
			   object will not take effect until after a reset."
            DEFVAL  {static}
        ::= { hmNet 7 }



-- WLAN MIB

    --
    --
    -- hmWLANParameter Group
    --

	hmWLANParameterState
		OBJECT-TYPE
			SYNTAX  	EnabledDisabledStatus
			MAX-ACCESS  read-write
			STATUS  	current
			DESCRIPTION
				"State of this interface. It may be enabled or disabled."
		::= { hmWLANParameter 1 }

	hmWLANParameterSSID
		OBJECT-TYPE
			SYNTAX  	OCTET STRING (SIZE(1..32))
			MAX-ACCESS  read-write
			STATUS  	current
			DESCRIPTION
				"SSID (Service Set Identifier) for this
				interface. An SSID can be up to 32 characters
				long. Only letters, digits and the special
				characters: '@!$%&/()=?{}[]+*~#-_.:,;<>' are
				allowed."
			::= { hmWLANParameter 3 }

	hmWLANParameterMode
		OBJECT-TYPE
			SYNTAX  INTEGER { a(1), b(2), bg(3), an(4), gn(5), bgn(6), abgn(7) }
			ACCESS  read-only
			STATUS  	current
			DESCRIPTION
				"Operation mode of this interface.
				1=802.11a
				2=802.11b
				3=802.11b/g
				4=802.11a/n
				5=802.11g/n
				6=802.11b/g/n
				7=802.11a/b/g/n"
		::= { hmWLANParameter 4 }

	hmWLANParameterChannel
		OBJECT-TYPE
			SYNTAX  	INTEGER(0..255)
			MAX-ACCESS  read-write
			STATUS  	current
			DESCRIPTION
				"Channel of this interface. This depends on
				your regional limitations and selected wlanMode.
				0 means any channel."
		::= { hmWLANParameter 5 }

    --
    --
    -- hmWLANSecurity Group
    --

	hmWLANSecurityMode
		OBJECT-TYPE
			SYNTAX  	INTEGER { none(0), wpapsk(1), wep64(2), wep128(3) }
			MAX-ACCESS  read-write
			STATUS  	current
			DESCRIPTION
				"Type of encryption of the wireless link.
				One of 'none', 'wpa-psk', 'wep64' or 'wep128'.
				If 'wpa-psk' is selected, the Encryption type
				will decide whether WPA or WPA2 is used. WPA
				and WPA2 can not be used at the same time"
		::= { hmWLANSecurity 1 }

	hmWLANSecurityWpaEncryptionAlgorithm
		OBJECT-TYPE
			SYNTAX  	INTEGER { none(0), tkip(1), aes(2), both(3) }
			MAX-ACCESS  read-write
			STATUS  	current
			DESCRIPTION
				"Encryption algorithm.
				1=TKIP is used on old hardware not supporting AES.
				2=AES is more secure and faster on station roaming."
		::= { hmWLANSecurity 2 }

	hmWLANSecurityWpaPsk
		OBJECT-TYPE
			SYNTAX  	OCTET STRING (SIZE(0..63))
			MAX-ACCESS  read-write
			STATUS  	current
			DESCRIPTION
				"Initial key for WPA encryption. NOTE: You should use a
				randomly generated alphanumeric sequence (up to 63 at least 8
				characters) for maximum security."
		::= { hmWLANSecurity 3 }

	hmWLANSecurityWepAuthType
		OBJECT-TYPE
			SYNTAX  	INTEGER { opensystem(0), sharedkey(1), wpawpa2psk(2) }
			MAX-ACCESS  read-write
			STATUS  	current
			DESCRIPTION
				"0=Open-System
				1=Shared-Key
				2=WPA-WPA2-PSK"
		::= { hmWLANSecurity 4 }

	hmWLANSecurityWepKeyEncoding
		OBJECT-TYPE
			SYNTAX  	INTEGER {hex(0), ascii(1) }
			MAX-ACCESS  read-write
			STATUS  	current
			DESCRIPTION
				"If this WEP passphrase is 'hex' or 'ascii'."
		::= { hmWLANSecurity 5 }

	hmWLANSecurityWepKey
		OBJECT-TYPE
			SYNTAX  	OCTET STRING (SIZE(5..26))
			MAX-ACCESS  read-write
			STATUS 		current
			DESCRIPTION
				"The WEP passphrase."
		::= { hmWLANSecurity 6 }

--Table of visible access points

	hmWLANVisibleAccessPointTable
		OBJECT-TYPE
			SYNTAX		SEQUENCE OF HmWLANVisibleAccessPointEntry
			MAX-ACCESS	not-accessible
			STATUS		current
			DESCRIPTION
				"Table of all VisibleAccessPoints to this interface."
		::= { hmWLAN 3 }

	hmWLANVisibleAccessPointEntry
		OBJECT-TYPE
			SYNTAX		HmWLANVisibleAccessPointEntry
			MAX-ACCESS	not-accessible
			STATUS	current
			DESCRIPTION
				"An entry (conceptual row) in the wlanVisibleAccessPointTable."
			INDEX      { hmWLANVisibleAccessPointEntryIdx }
    ::= { hmWLANVisibleAccessPointTable 1 }

	HmWLANVisibleAccessPointEntry ::=
		SEQUENCE 	{
			hmWLANVisibleAccessPointEntryIdx
				INTEGER,
			hmWLANVisibleAccessPointEntrySNR
				INTEGER,
			hmWLANVisibleAccessPointEntryChannel
				INTEGER,
			hmWLANVisibleAccessPointEntryPower
				INTEGER,
			hmWLANVisibleAccessPointEntrySSID
				OCTET STRING,
			hmWLANVisibleAccessPointEntrySecurity
				OCTET STRING,
			hmWLANVisibleAccessPointEntryAddress
				MacAddress,
			hmWLANVisibleAccessPointEntryConnected
				INTEGER,
			hmWLANVisibleAccessPointEntryRSSI
				INTEGER,
			hmWLANVisibleAccessPointEntryNoise
				INTEGER
		}

	hmWLANVisibleAccessPointEntryIdx
		OBJECT-TYPE
			SYNTAX		INTEGER (0..49)
			MAX-ACCESS	not-accessible
			STATUS		current
			DESCRIPTION
				"Index in the wlanVisibleAccessPointTableIf1."
		::= { hmWLANVisibleAccessPointEntry 1 }

	hmWLANVisibleAccessPointEntrySNR
		OBJECT-TYPE
			SYNTAX		INTEGER
			MAX-ACCESS	read-only
			STATUS		current
			DESCRIPTION
				"SNR of this visible access point."
		::= { hmWLANVisibleAccessPointEntry 2 }

	hmWLANVisibleAccessPointEntryChannel
		OBJECT-TYPE
			SYNTAX		INTEGER (0..255)
			MAX-ACCESS	read-only
			STATUS		current
			DESCRIPTION
				"TX-Rate of this visible access point."
		::= { hmWLANVisibleAccessPointEntry 3 }

	hmWLANVisibleAccessPointEntryPower
		OBJECT-TYPE
			SYNTAX		INTEGER (0..255)
			MAX-ACCESS	read-only
			STATUS		current
			DESCRIPTION
				"TX-Power of this visible access point."
		::= { hmWLANVisibleAccessPointEntry 4 }

	hmWLANVisibleAccessPointEntrySSID
		OBJECT-TYPE
			SYNTAX		OCTET STRING
			MAX-ACCESS	read-only
			STATUS		current
			DESCRIPTION
				"SSID of this visible access point."
		::= { hmWLANVisibleAccessPointEntry 5 }

	hmWLANVisibleAccessPointEntrySecurity
		OBJECT-TYPE
			SYNTAX		OCTET STRING
			MAX-ACCESS	read-only
			STATUS		current
			DESCRIPTION
				"Security of this visible access point."
		::= { hmWLANVisibleAccessPointEntry 6 }

	hmWLANVisibleAccessPointEntryAddress
		OBJECT-TYPE
			SYNTAX		MacAddress
			MAX-ACCESS	read-only
			STATUS		current
			DESCRIPTION
				"MAC address of this visible access point."
		::= { hmWLANVisibleAccessPointEntry 7 }

	hmWLANVisibleAccessPointEntryConnected
		OBJECT-TYPE
			SYNTAX		INTEGER (0..1)
			MAX-ACCESS	read-only
			STATUS		current
			DESCRIPTION
				"SNR of this visible access point."
		::= { hmWLANVisibleAccessPointEntry 8 }

	hmWLANVisibleAccessPointEntryRSSI
		OBJECT-TYPE
			SYNTAX		INTEGER
			MAX-ACCESS	read-only
			STATUS		current
			DESCRIPTION
				"This object gives back the RSSI value, i.e. the signal
				strength of the visible AP. "
		::= { hmWLANVisibleAccessPointEntry 9 }

	hmWLANVisibleAccessPointEntryNoise
		OBJECT-TYPE
			SYNTAX		INTEGER
			MAX-ACCESS	read-only
			STATUS		current
			DESCRIPTION
				"This value shows the noise floor for the connection to the
				visible AP."
		::= { hmWLANVisibleAccessPointEntry 10 }

END
