------------------------------------------------------------------------------
--
--  File         : HMIT-SW-FDB-MIB.mib
--  Description  :
--  Version      :
-- 	Copyright    : Copyright ⓒ 2019 Belden Singapore Pte Ltd., All rights reserved.
--
-- $Id:
--
------------------------------------------------------------------------------

------------------------------------------------------------------------------
HMIT-SW-FDB-MIB DEFINITIONS ::= BEGIN


IMPORTS
        MODULE-IDENTITY, OBJECT-TYPE, NOTIFICATION-TYPE, Counter32, Gauge32,
        Integer32, Unsigned32, IpAddress,Counter64
        	                                    FROM SNMPv2-SMI
        TEXTUAL-CONVENTION, TruthValue, MacAddress,
	RowStatus, DisplayString
                                                 FROM SNMPv2-TC
        MODULE-COMPLIANCE, OBJECT-GROUP
        	FROM SNMPv2-CONF
        hmITSwitchTech
        	FROM HMIT-SMI;

hmITSwFDB     MODULE-IDENTITY
            	LAST-UPDATED 	"201001081700Z"
            	ORGANIZATION 	"Belden Singapore Pte Ltd."
            	CONTACT-INFO
            		"Belden Singapore Pte Ltd."
            	DESCRIPTION
            		"FDB Module."
				REVISION "201001081700Z"
				DESCRIPTION
					"The initial revision of this mib module "
				::= { hmITSwitchTech  12 }




------------------------------------------------------------------------------

hmITSwFDBAgingTime    	OBJECT-TYPE
                    		SYNTAX  INTEGER(0..1000000)
                    		MAX-ACCESS  read-write
                    		STATUS  current
                    		DESCRIPTION
                    			"Dynamic MAC ageing time"
                    		::= { hmITSwFDB 1 }

hmITSwFDBSytemMacLimit	OBJECT-TYPE
                    		SYNTAX  INTEGER(1..32767)
                    		MAX-ACCESS  read-write
                    		STATUS  current
                    		DESCRIPTION
                    			"Limit"
                    		::= { hmITSwFDB 2 }

hmITSwFDBVlanMacLearnTable	OBJECT-TYPE
                    		SYNTAX  SEQUENCE OF  HmITSwFDBVlanMacLearnEntry
                    		MAX-ACCESS  not-accessible
                    		STATUS  current
                    		DESCRIPTION
                    			"MAC table of VLAN"
                    		::= { hmITSwFDB 3 }

hmITSwFDBVlanMacLearnEntry	OBJECT-TYPE
                    		SYNTAX  HmITSwFDBVlanMacLearnEntry
                    		MAX-ACCESS  not-accessible
                    		STATUS  current
                    		DESCRIPTION
                    			"MAC table of VLAN"
                    		INDEX  { hmITSwFDBmacLearnVlan }
                    		::= { hmITSwFDBVlanMacLearnTable 1 }

HmITSwFDBVlanMacLearnEntry	::= SEQUENCE {
                    			hmITSwFDBmacLearnVlan    INTEGER,
                    			hmITSwFDBmacLearnNum     INTEGER,
                    			hmITSwFDBmacLearnStatus   RowStatus
                    	             }


hmITSwFDBmacLearnVlan 	OBJECT-TYPE
                    		SYNTAX  INTEGER (1..4096)
                    		MAX-ACCESS  read-only
                    		STATUS  current
                    		DESCRIPTION
                    			"port"
                    		::= { hmITSwFDBVlanMacLearnEntry 1 }

hmITSwFDBmacLearnNum  	OBJECT-TYPE
                    		SYNTAX  INTEGER(1..32767)
                    		MAX-ACCESS  read-write
                    		STATUS  current
                    		DESCRIPTION
                    			"Limit MAC number"
                    		::= { hmITSwFDBVlanMacLearnEntry 2 }

hmITSwFDBmacLearnStatus	OBJECT-TYPE
                    		SYNTAX  RowStatus
                    		MAX-ACCESS  read-write
                    		STATUS  current
                    		DESCRIPTION
                    			"low status"
                    		::= { hmITSwFDBVlanMacLearnEntry 3 }

hmITSwFDBPortMacLearnTable	OBJECT-TYPE
                    		SYNTAX  SEQUENCE OF  HmITSwFDBPortMacLearnEntry
                    		MAX-ACCESS  not-accessible
                    		STATUS  current
                    		DESCRIPTION
                    			"MAC table of Port"
                    		::= { hmITSwFDB 9 }

hmITSwFDBPortMacLearnEntry	OBJECT-TYPE
                    		SYNTAX  HmITSwFDBPortMacLearnEntry
                    		MAX-ACCESS  not-accessible
                    		STATUS  current
                    		DESCRIPTION
                    			"MAC table of Port"
                    		INDEX  { hmITSwFDBmacLearnPort }
                    		::= { hmITSwFDBPortMacLearnTable 1 }

HmITSwFDBPortMacLearnEntry	::= SEQUENCE {
                    			hmITSwFDBmacLearnPort    INTEGER,
                    			hmITSwFDBPortmacLearnNum     INTEGER,
                    			hmITSwFDBPortmacLearnStatus   RowStatus
                    	             }


hmITSwFDBmacLearnPort 	OBJECT-TYPE
                    		SYNTAX  INTEGER (1..2147483647)
                    		MAX-ACCESS  read-only
                    		STATUS  current
                    		DESCRIPTION
                    			"port"
                    		::= { hmITSwFDBPortMacLearnEntry 1 }
hmITSwFDBPortmacLearnNum  	OBJECT-TYPE
                    		SYNTAX  INTEGER(1..32767)
                    		MAX-ACCESS  read-write
                    		STATUS  current
                    		DESCRIPTION
                    			"Limit MAC number"
                    		::= { hmITSwFDBPortMacLearnEntry 2 }

hmITSwFDBPortmacLearnStatus	OBJECT-TYPE
                    		SYNTAX  RowStatus
                    		MAX-ACCESS  read-write
                    		STATUS  current
                    		DESCRIPTION
                    			"low status"
                    		::= { hmITSwFDBPortMacLearnEntry 3 }

hmITSwFDBFdbTable     	OBJECT-TYPE
                    		SYNTAX  SEQUENCE OF  HmITSwFDBFdbEntry
                    		MAX-ACCESS  not-accessible
                    		STATUS  current
                    		DESCRIPTION
                    			"MAC table"
                    		::= { hmITSwFDB 10 }

hmITSwFDBFdbEntry     	OBJECT-TYPE
                    		SYNTAX  HmITSwFDBFdbEntry
                    		MAX-ACCESS  not-accessible
                    		STATUS  current
                    		DESCRIPTION
                    			"MAC table"
                    		INDEX  { hmITSwFDBfdbMacAddr,  hmITSwFDBfdbVlanId, hmITSwFDBfdbPort, hmITSwFDBfdbType }
                    		::= { hmITSwFDBFdbTable 1 }

HmITSwFDBFdbEntry     	::= SEQUENCE {
                    			hmITSwFDBfdbMacAddr      MacAddress,
                    			hmITSwFDBfdbVlanId       INTEGER,
                    			hmITSwFDBfdbPort         INTEGER,
                    			hmITSwFDBfdbType         INTEGER,
                    			hmITSwFDBfdbState        INTEGER,
                    			hmITSwFDBfdbStatus       RowStatus
                    	             }


hmITSwFDBfdbMacAddr   	OBJECT-TYPE
                    		SYNTAX  MacAddress
                    		MAX-ACCESS  read-write
                    		STATUS  current
                    		DESCRIPTION
                    			"MAC address"
                    		::= { hmITSwFDBFdbEntry 1 }

hmITSwFDBfdbVlanId    	OBJECT-TYPE
                    		SYNTAX  INTEGER(1..4094)
                    		MAX-ACCESS  read-write
                    		STATUS  current
                    		DESCRIPTION
                    			"VLAN ID"
                    		::= { hmITSwFDBFdbEntry 2 }

hmITSwFDBfdbPort      	OBJECT-TYPE
                    		SYNTAX  INTEGER (1..2147483647)
                    		MAX-ACCESS  read-write
                    		STATUS  current
                    		DESCRIPTION
                    			"port ID"
                    		::= { hmITSwFDBFdbEntry 3 }

hmITSwFDBfdbType      	OBJECT-TYPE
                    		SYNTAX  INTEGER(1..3)
                    		MAX-ACCESS  read-write
                    		STATUS  current
                    		DESCRIPTION
                    			"MAC type(1 static, 2 fiter, 3 dynamic )"
                    		::= { hmITSwFDBFdbEntry 4 }

hmITSwFDBfdbState     	OBJECT-TYPE
                    		SYNTAX  INTEGER(0..4)
                    		MAX-ACCESS  read-only
                    		STATUS  current
                    		DESCRIPTION
                    			"MAC status(0 drop, 1 FWD, 2 toCPU, 3 FWD and toCPU, 4 toCPU remark L3)"
                    		::= { hmITSwFDBFdbEntry 5 }

hmITSwFDBfdbStatus    	OBJECT-TYPE
                    		SYNTAX  RowStatus
                    		MAX-ACCESS  read-only
                    		STATUS  current
                    		DESCRIPTION
                    			"low status"
                    		::= { hmITSwFDBFdbEntry 6 }

hmITSwFDBDelPortindex 	OBJECT-TYPE
                    		SYNTAX  INTEGER(1..32768)
                    		MAX-ACCESS  read-write
                    		STATUS  current
                    		DESCRIPTION
                    			"logic port"
                    		::= { hmITSwFDB 13 }

hmITSwFDBDelVlanindex 	OBJECT-TYPE
                    		SYNTAX  INTEGER(1..4094)
                    		MAX-ACCESS  read-write
                    		STATUS  current
                    		DESCRIPTION
                    			"vid index"
                    		::= { hmITSwFDB 14 }

hmITSwFDBDelPortVlanindex	OBJECT-TYPE
                    		SYNTAX  DisplayString(SIZE(3..10))
                    		MAX-ACCESS  read-write
                    		STATUS  current
                    		DESCRIPTION
                    			"logic port index and vid index"
                    		::= { hmITSwFDB 15 }





END
