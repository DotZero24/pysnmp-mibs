------------------------------------------------------------------------------
--
--  File         : HMIT-IP-MIB.mib
--  Description  :
--  Version      :
--  Copyright    : Copyright ⓒ 2019 Belden Singapore Pte Ltd. All rights reserved.
--
-- $Id:
--
------------------------------------------------------------------------------

------------------------------------------------------------------------------
HMIT-IP-MIB DEFINITIONS ::= BEGIN


IMPORTS
        MODULE-IDENTITY, OBJECT-TYPE, NOTIFICATION-TYPE, Counter32, Gauge32,
        Integer32, Unsigned32, TimeTicks,IpAddress,Counter64
        	                                    FROM SNMPv2-SMI
        TEXTUAL-CONVENTION, TruthValue, MacAddress,
	RowStatus, DisplayString, DateAndTime
                                                 FROM SNMPv2-TC
        MODULE-COMPLIANCE, OBJECT-GROUP
        	FROM SNMPv2-CONF
        hmITMgmt
        	FROM HMIT-SMI;



hmITIpMib             	MODULE-IDENTITY
							LAST-UPDATED "201001081700Z"
                    		ORGANIZATION 	"Belden Singapore Pte Ltd."
                    		CONTACT-INFO
                    			"Belden Singapore Pte Ltd."
							DESCRIPTION
								"Ip MIB."
							REVISION "201001081700Z"
                    		DESCRIPTION
                      			"The initial revision of this mib module "
                    		::= { hmITMgmt  700 }



hmITIpTable           	OBJECT-TYPE
                    		SYNTAX  SEQUENCE OF   HmITIpEntry
                    		MAX-ACCESS  not-accessible
                    		STATUS  current
                    		DESCRIPTION
                    			"IP Table"
                    		::= { hmITIpMib 1 }

hmITIpEntry           	OBJECT-TYPE
                    		SYNTAX  HmITIpEntry
                    		MAX-ACCESS  not-accessible
                    		STATUS  current
                    		DESCRIPTION
                    			"Ip Table Entry"
                    		INDEX  { hmITIpTIfName, hmITIpTAddress, hmITIpTMask }
                    		::= { hmITIpTable 1 }

HmITIpEntry           	::= SEQUENCE {
                    			hmITIpTIfName            DisplayString,
                    			hmITIpTAddress           IpAddress,
                    			hmITIpTMask              IpAddress,
                    			hmITIpTBPAddress         IpAddress,
                    			hmITIpTType              INTEGER,
                    			hmITIpTWay               INTEGER,
                    			hmITIpTRowStatus         RowStatus
                    	             }


hmITIpTIfName         	OBJECT-TYPE
                    		SYNTAX  DisplayString(SIZE(0..40))
                    		MAX-ACCESS  not-accessible
                    		STATUS  current
                    		DESCRIPTION
                    			"Interface name"
                    		::= { hmITIpEntry 1 }

hmITIpTAddress        	OBJECT-TYPE
                    		SYNTAX  IpAddress
                    		MAX-ACCESS  not-accessible
                    		STATUS  current
                    		DESCRIPTION
                    			"Interface ip address"
                    		::= { hmITIpEntry 2 }

hmITIpTMask           	OBJECT-TYPE
                    		SYNTAX  IpAddress
                    		MAX-ACCESS  not-accessible
                    		STATUS  current
                    		DESCRIPTION
                    			"Ip mask"
                    		::= { hmITIpEntry 3 }

hmITIpTBPAddress      	OBJECT-TYPE
                    		SYNTAX  IpAddress
                    		MAX-ACCESS  read-only
                    		STATUS  current
                    		DESCRIPTION
                    			"Ip broadcast address"
                    		::= { hmITIpEntry 4 }

hmITIpTType           	OBJECT-TYPE
                    		SYNTAX  INTEGER {
                    			         primary(1),
                    			          secondary(2)
                    			        }
                    		MAX-ACCESS  read-only
                    		STATUS  current
                    		DESCRIPTION
                    			"Ip type"
                    		::= { hmITIpEntry 5 }

hmITIpTWay            	OBJECT-TYPE
                    		SYNTAX  INTEGER {
                    			         manual(1),
                    			          dhcp(2),
                    			          negotiated(3),
                    			          unnumbered(4),
                    			          virtual(5)
                    			        }
                    		MAX-ACCESS  read-only
                    		STATUS  current
                    		DESCRIPTION
                    			"Ip config type"
                    		::= { hmITIpEntry 6 }

hmITIpTRowStatus      	OBJECT-TYPE
                    		SYNTAX  RowStatus
                    		MAX-ACCESS  read-create
                    		STATUS  current
                    		DESCRIPTION
                    			"Row status"
                    		::= { hmITIpEntry 7 }



END
