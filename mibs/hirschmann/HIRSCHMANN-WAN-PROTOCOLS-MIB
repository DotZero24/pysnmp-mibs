HIRSCHMANN-WAN-PROTOCOLS-MIB DEFINITIONS ::= BEGIN

IMPORTS
    MODULE-IDENTITY, enterprises, Unsigned32
        FROM SNMPv2-SMI -- RFC 2578
    TEXTUAL-CONVENTION
        FROM SNMPv2-TC  -- RFC 2579
    hmWanMib, hmWanMgmt
    	FROM HIRSCHMANN-WAN-MIB;

hmWanProtocolsMib MODULE-IDENTITY
	LAST-UPDATED "201610130000Z" -- October 13, 2016
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Copyright (C) 2015. All Rights Reserved."
    REVISION     "201502130000Z" -- Februar 13, 2015
    DESCRIPTION
         "Initial version."
    ::= { hmWanMgmt 2 }

hmWanXccnt			OBJECT IDENTIFIER ::= { hmWanProtocolsMib 1 }

hmWanXccntAn1		OBJECT-TYPE
			SYNTAX	INTEGER
			MAX-ACCESS	read-only
			STATUS	current
			::= { hmWanXccnt 1 }

hmWanXccntAn2		OBJECT-TYPE
			SYNTAX	INTEGER
			MAX-ACCESS	read-only
			STATUS	current
			::= { hmWanXccnt 2 }

hmWanXccntCnt1		OBJECT-TYPE
			SYNTAX	Counter32
			MAX-ACCESS	read-only
			STATUS	current
			::= { hmWanXccnt 3 }

hmWanXccntCnt2		OBJECT-TYPE
			SYNTAX	Counter32
			MAX-ACCESS	read-only
			STATUS	current
			::= { hmWanXccnt 4 }

hmWanXccntBin1		OBJECT-TYPE
			SYNTAX	Gauge32
			MAX-ACCESS	read-only
			STATUS	current
			::= { hmWanXccnt 5 }

hmWanXccntBin2		OBJECT-TYPE
			SYNTAX	Gauge32
			MAX-ACCESS	read-only
			STATUS	current
			::= { hmWanXccnt 6 }

hmWanXccntBin3		OBJECT-TYPE
			SYNTAX	Gauge32
			MAX-ACCESS	read-only
			STATUS	current
			::= { hmWanXccnt 7 }

hmWanXccntBin4		OBJECT-TYPE
			SYNTAX	Gauge32
			MAX-ACCESS	read-only
			STATUS	current
			::= { hmWanXccnt 8 }

hmWanXccntOut1		OBJECT-TYPE
			SYNTAX	Gauge32
			MAX-ACCESS	read-write
			STATUS	current
			::= { hmWanXccnt 9 }

hmWanMbus	OBJECT IDENTIFIER ::= { hmWanProtocolsMib 2 }
hmWanMbus00	OBJECT IDENTIFIER ::= { hmWanMbus 0 }

hmWanMbus00IdNumber		OBJECT-TYPE
			SYNTAX	Gauge32
			MAX-ACCESS	read-only
			STATUS	current
			::= { hmWanMbus00 1 }

hmWanMbus00Manufacturer	OBJECT-TYPE
			SYNTAX	Gauge32
			MAX-ACCESS	read-only
			STATUS	current
			::= { hmWanMbus00 2 }

hmWanMbus00Version		OBJECT-TYPE
			SYNTAX	Gauge32
			MAX-ACCESS	read-only
			STATUS	current
			::= { hmWanMbus00 3 }

hmWanMbus00Medium		OBJECT-TYPE
			SYNTAX	Gauge32
			MAX-ACCESS	read-only
			STATUS	current
			::= { hmWanMbus00 4 }

hmWanMbus00Status		OBJECT-TYPE
			SYNTAX	Gauge32
			MAX-ACCESS	read-only
			STATUS	current
			::= { hmWanMbus00 5 }

hmWanMbus00VIF00		OBJECT-TYPE
			SYNTAX	INTEGER
			MAX-ACCESS	read-only
			STATUS	current
			::= { hmWanMbus00 6 }

hmWanMbus00Value00		OBJECT-TYPE
			SYNTAX	INTEGER
			MAX-ACCESS	read-only
			STATUS	current
			::= { hmWanMbus00 7 }

hmWanMbus00VIF01		OBJECT-TYPE
			SYNTAX	INTEGER
			MAX-ACCESS	read-only
			STATUS	current
			::= { hmWanMbus00 8 }

hmWanMbus00Value01		OBJECT-TYPE
			SYNTAX	INTEGER
			MAX-ACCESS	read-only
			STATUS	current
			::= { hmWanMbus00 9 }

hmWanMbus00VIF02		OBJECT-TYPE
			SYNTAX	INTEGER
			MAX-ACCESS	read-only
			STATUS	current
			::= { hmWanMbus00 10 }

hmWanMbus00Value02		OBJECT-TYPE
			SYNTAX	INTEGER
			MAX-ACCESS	read-only
			STATUS	current
			::= { hmWanMbus00 11 }

hmWanMbus00VIF03		OBJECT-TYPE
			SYNTAX	INTEGER
			MAX-ACCESS	read-only
			STATUS	current
			::= { hmWanMbus00 12 }

hmWanMbus00Value03		OBJECT-TYPE
			SYNTAX	INTEGER
			MAX-ACCESS	read-only
			STATUS	current
			::= { hmWanMbus00 13 }

hmWanMbus00VIF04		OBJECT-TYPE
			SYNTAX	INTEGER
			MAX-ACCESS	read-only
			STATUS	current
			::= { hmWanMbus00 14 }

hmWanMbus00Value04		OBJECT-TYPE
			SYNTAX	INTEGER
			MAX-ACCESS	read-only
			STATUS	current
			::= { hmWanMbus00 15 }

hmWanMbus00VIF05		OBJECT-TYPE
			SYNTAX	INTEGER
			MAX-ACCESS	read-only
			STATUS	current
			::= { hmWanMbus00 16 }

hmWanMbus00Value05		OBJECT-TYPE
			SYNTAX	INTEGER
			MAX-ACCESS	read-only
			STATUS	current
			::= { hmWanMbus00 17 }

hmWanMbus00VIF06		OBJECT-TYPE
			SYNTAX	INTEGER
			MAX-ACCESS	read-only
			STATUS	current
			::= { hmWanMbus00 18 }

hmWanMbus00Value06		OBJECT-TYPE
			SYNTAX	INTEGER
			MAX-ACCESS	read-only
			STATUS	current
			::= { hmWanMbus00 19 }

hmWanMbus00VIF07		OBJECT-TYPE
			SYNTAX	INTEGER
			MAX-ACCESS	read-only
			STATUS	current
			::= { hmWanMbus00 20 }

hmWanMbus00Value07		OBJECT-TYPE
			SYNTAX	INTEGER
			MAX-ACCESS	read-only
			STATUS	current
			::= { hmWanMbus00 21 }

hmWanMbus00VIF08		OBJECT-TYPE
			SYNTAX	INTEGER
			MAX-ACCESS	read-only
			STATUS	current
			::= { hmWanMbus00 22 }

hmWanMbus00Value08		OBJECT-TYPE
			SYNTAX	INTEGER
			MAX-ACCESS	read-only
			STATUS	current
			::= { hmWanMbus00 23 }

hmWanMbus00VIF09		OBJECT-TYPE
			SYNTAX	INTEGER
			MAX-ACCESS	read-only
			STATUS	current
			::= { hmWanMbus00 24 }

hmWanMbus00Value09		OBJECT-TYPE
			SYNTAX	INTEGER
			MAX-ACCESS	read-only
			STATUS	current
			::= { hmWanMbus00 25 }

hmWanMbus00VIF0A		OBJECT-TYPE
			SYNTAX	INTEGER
			MAX-ACCESS	read-only
			STATUS	current
			::= { hmWanMbus00 26 }

hmWanMbus00Value0A		OBJECT-TYPE
			SYNTAX	INTEGER
			MAX-ACCESS	read-only
			STATUS	current
			::= { hmWanMbus00 27 }

hmWanMbus00VIF0B		OBJECT-TYPE
			SYNTAX	INTEGER
			MAX-ACCESS	read-only
			STATUS	current
			::= { hmWanMbus00 28 }

hmWanMbus00Value0B		OBJECT-TYPE
			SYNTAX	INTEGER
			MAX-ACCESS	read-only
			STATUS	current
			::= { hmWanMbus00 29 }

hmWanMbus00VIF0C		OBJECT-TYPE
			SYNTAX	INTEGER
			MAX-ACCESS	read-only
			STATUS	current
			::= { hmWanMbus00 30 }

hmWanMbus00Value0C		OBJECT-TYPE
			SYNTAX	INTEGER
			MAX-ACCESS	read-only
			STATUS	current
			::= { hmWanMbus00 31 }

hmWanMbus00VIF0D		OBJECT-TYPE
			SYNTAX	INTEGER
			MAX-ACCESS	read-only
			STATUS	current
			::= { hmWanMbus00 32 }

hmWanMbus00Value0D		OBJECT-TYPE
			SYNTAX	INTEGER
			MAX-ACCESS	read-only
			STATUS	current
			::= { hmWanMbus00 33 }

hmWanMbus00VIF0E		OBJECT-TYPE
			SYNTAX	INTEGER
			MAX-ACCESS	read-only
			STATUS	current
			::= { hmWanMbus00 34 }

hmWanMbus00Value0E		OBJECT-TYPE
			SYNTAX	INTEGER
			MAX-ACCESS	read-only
			STATUS	current
			::= { hmWanMbus00 35 }

hmWanMbus00VIF0F		OBJECT-TYPE
			SYNTAX	INTEGER
			MAX-ACCESS	read-only
			STATUS	current
			::= { hmWanMbus00 36 }

hmWanMbus00Value0F		OBJECT-TYPE
			SYNTAX	INTEGER
			MAX-ACCESS	read-only
			STATUS	current
			::= { hmWanMbus00 37 }

hmWanMbus00VIF10		OBJECT-TYPE
			SYNTAX	INTEGER
			MAX-ACCESS	read-only
			STATUS	current
			::= { hmWanMbus00 38 }

hmWanMbus00Value10		OBJECT-TYPE
			SYNTAX	INTEGER
			MAX-ACCESS	read-only
			STATUS	current
			::= { hmWanMbus00 39 }

hmWanMbus00VIF11		OBJECT-TYPE
			SYNTAX	INTEGER
			MAX-ACCESS	read-only
			STATUS	current
			::= { hmWanMbus00 40 }

hmWanMbus00Value11		OBJECT-TYPE
			SYNTAX	INTEGER
			MAX-ACCESS	read-only
			STATUS	current
			::= { hmWanMbus00 41 }

hmWanMbus00VIF12		OBJECT-TYPE
			SYNTAX	INTEGER
			MAX-ACCESS	read-only
			STATUS	current
			::= { hmWanMbus00 42 }

hmWanMbus00Value12		OBJECT-TYPE
			SYNTAX	INTEGER
			MAX-ACCESS	read-only
			STATUS	current
			::= { hmWanMbus00 43 }

hmWanMbus00VIF13		OBJECT-TYPE
			SYNTAX	INTEGER
			MAX-ACCESS	read-only
			STATUS	current
			::= { hmWanMbus00 44 }

hmWanMbus00Value13		OBJECT-TYPE
			SYNTAX	INTEGER
			MAX-ACCESS	read-only
			STATUS	current
			::= { hmWanMbus00 45 }

hmWanMbus00VIF14		OBJECT-TYPE
			SYNTAX	INTEGER
			MAX-ACCESS	read-only
			STATUS	current
			::= { hmWanMbus00 46 }

hmWanMbus00Value14		OBJECT-TYPE
			SYNTAX	INTEGER
			MAX-ACCESS	read-only
			STATUS	current
			::= { hmWanMbus00 47 }

hmWanMbus00VIF15		OBJECT-TYPE
			SYNTAX	INTEGER
			MAX-ACCESS	read-only
			STATUS	current
			::= { hmWanMbus00 48 }

hmWanMbus00Value15		OBJECT-TYPE
			SYNTAX	INTEGER
			MAX-ACCESS	read-only
			STATUS	current
			::= { hmWanMbus00 49 }

hmWanMbus00VIF16		OBJECT-TYPE
			SYNTAX	INTEGER
			MAX-ACCESS	read-only
			STATUS	current
			::= { hmWanMbus00 50 }

hmWanMbus00Value16		OBJECT-TYPE
			SYNTAX	INTEGER
			MAX-ACCESS	read-only
			STATUS	current
			::= { hmWanMbus00 51 }

hmWanMbus00VIF17		OBJECT-TYPE
			SYNTAX	INTEGER
			MAX-ACCESS	read-only
			STATUS	current
			::= { hmWanMbus00 52 }

hmWanMbus00Value17		OBJECT-TYPE
			SYNTAX	INTEGER
			MAX-ACCESS	read-only
			STATUS	current
			::= { hmWanMbus00 53 }

hmWanMbus00VIF18		OBJECT-TYPE
			SYNTAX	INTEGER
			MAX-ACCESS	read-only
			STATUS	current
			::= { hmWanMbus00 54 }

hmWanMbus00Value18		OBJECT-TYPE
			SYNTAX	INTEGER
			MAX-ACCESS	read-only
			STATUS	current
			::= { hmWanMbus00 55 }

hmWanMbus00VIF19		OBJECT-TYPE
			SYNTAX	INTEGER
			MAX-ACCESS	read-only
			STATUS	current
			::= { hmWanMbus00 56 }

hmWanMbus00Value19		OBJECT-TYPE
			SYNTAX	INTEGER
			MAX-ACCESS	read-only
			STATUS	current
			::= { hmWanMbus00 57 }

hmWanMbus00VIF1A		OBJECT-TYPE
			SYNTAX	INTEGER
			MAX-ACCESS	read-only
			STATUS	current
			::= { hmWanMbus00 58 }

hmWanMbus00Value1A		OBJECT-TYPE
			SYNTAX	INTEGER
			MAX-ACCESS	read-only
			STATUS	current
			::= { hmWanMbus00 59 }

hmWanMbus00VIF1B		OBJECT-TYPE
			SYNTAX	INTEGER
			MAX-ACCESS	read-only
			STATUS	current
			::= { hmWanMbus00 60 }

hmWanMbus00Value1B		OBJECT-TYPE
			SYNTAX	INTEGER
			MAX-ACCESS	read-only
			STATUS	current
			::= { hmWanMbus00 61 }

hmWanMbus00VIF1C		OBJECT-TYPE
			SYNTAX	INTEGER
			MAX-ACCESS	read-only
			STATUS	current
			::= { hmWanMbus00 62 }

hmWanMbus00Value1C		OBJECT-TYPE
			SYNTAX	INTEGER
			MAX-ACCESS	read-only
			STATUS	current
			::= { hmWanMbus00 63 }

hmWanMbus00VIF1D		OBJECT-TYPE
			SYNTAX	INTEGER
			MAX-ACCESS	read-only
			STATUS	current
			::= { hmWanMbus00 64 }

hmWanMbus00Value1D		OBJECT-TYPE
			SYNTAX	INTEGER
			MAX-ACCESS	read-only
			STATUS	current
			::= { hmWanMbus00 65 }

hmWanMbus00VIF1E		OBJECT-TYPE
			SYNTAX	INTEGER
			MAX-ACCESS	read-only
			STATUS	current
			::= { hmWanMbus00 66 }

hmWanMbus00Value1E		OBJECT-TYPE
			SYNTAX	INTEGER
			MAX-ACCESS	read-only
			STATUS	current
			::= { hmWanMbus00 67 }

hmWanMbus00VIF1F		OBJECT-TYPE
			SYNTAX	INTEGER
			MAX-ACCESS	read-only
			STATUS	current
			::= { hmWanMbus00 68 }

hmWanMbus00Value1F		OBJECT-TYPE
			SYNTAX	INTEGER
			MAX-ACCESS	read-only
			STATUS	current
			::= { hmWanMbus00 69 }

hmWanMbus00VIF20		OBJECT-TYPE
			SYNTAX	INTEGER
			MAX-ACCESS	read-only
			STATUS	current
			::= { hmWanMbus00 70 }

hmWanMbus00Value20		OBJECT-TYPE
			SYNTAX	INTEGER
			MAX-ACCESS	read-only
			STATUS	current
			::= { hmWanMbus00 71 }

hmWanMbus00VIF21		OBJECT-TYPE
			SYNTAX	INTEGER
			MAX-ACCESS	read-only
			STATUS	current
			::= { hmWanMbus00 72 }

hmWanMbus00Value21		OBJECT-TYPE
			SYNTAX	INTEGER
			MAX-ACCESS	read-only
			STATUS	current
			::= { hmWanMbus00 73 }

hmWanMbus00VIF22		OBJECT-TYPE
			SYNTAX	INTEGER
			MAX-ACCESS	read-only
			STATUS	current
			::= { hmWanMbus00 74 }

hmWanMbus00Value22		OBJECT-TYPE
			SYNTAX	INTEGER
			MAX-ACCESS	read-only
			STATUS	current
			::= { hmWanMbus00 75 }

hmWanMbus00VIF23		OBJECT-TYPE
			SYNTAX	INTEGER
			MAX-ACCESS	read-only
			STATUS	current
			::= { hmWanMbus00 76 }

hmWanMbus00Value23		OBJECT-TYPE
			SYNTAX	INTEGER
			MAX-ACCESS	read-only
			STATUS	current
			::= { hmWanMbus00 77 }

hmWanMbus00VIF24		OBJECT-TYPE
			SYNTAX	INTEGER
			MAX-ACCESS	read-only
			STATUS	current
			::= { hmWanMbus00 78 }

hmWanMbus00Value24		OBJECT-TYPE
			SYNTAX	INTEGER
			MAX-ACCESS	read-only
			STATUS	current
			::= { hmWanMbus00 79 }

hmWanMbus00VIF25		OBJECT-TYPE
			SYNTAX	INTEGER
			MAX-ACCESS	read-only
			STATUS	current
			::= { hmWanMbus00 80 }

hmWanMbus00Value25		OBJECT-TYPE
			SYNTAX	INTEGER
			MAX-ACCESS	read-only
			STATUS	current
			::= { hmWanMbus00 81 }

hmWanMbus00VIF26		OBJECT-TYPE
			SYNTAX	INTEGER
			MAX-ACCESS	read-only
			STATUS	current
			::= { hmWanMbus00 82 }

hmWanMbus00Value26		OBJECT-TYPE
			SYNTAX	INTEGER
			MAX-ACCESS	read-only
			STATUS	current
			::= { hmWanMbus00 83 }

hmWanMbus00VIF27		OBJECT-TYPE
			SYNTAX	INTEGER
			MAX-ACCESS	read-only
			STATUS	current
			::= { hmWanMbus00 84 }

hmWanMbus00Value27		OBJECT-TYPE
			SYNTAX	INTEGER
			MAX-ACCESS	read-only
			STATUS	current
			::= { hmWanMbus00 85 }

hmWanMbus00VIF28		OBJECT-TYPE
			SYNTAX	INTEGER
			MAX-ACCESS	read-only
			STATUS	current
			::= { hmWanMbus00 86 }

hmWanMbus00Value28		OBJECT-TYPE
			SYNTAX	INTEGER
			MAX-ACCESS	read-only
			STATUS	current
			::= { hmWanMbus00 87 }

hmWanMbus00VIF29		OBJECT-TYPE
			SYNTAX	INTEGER
			MAX-ACCESS	read-only
			STATUS	current
			::= { hmWanMbus00 88 }

hmWanMbus00Value29		OBJECT-TYPE
			SYNTAX	INTEGER
			MAX-ACCESS	read-only
			STATUS	current
			::= { hmWanMbus00 89 }

hmWanMbus00VIF2A		OBJECT-TYPE
			SYNTAX	INTEGER
			MAX-ACCESS	read-only
			STATUS	current
			::= { hmWanMbus00 90 }

hmWanMbus00Value2A		OBJECT-TYPE
			SYNTAX	INTEGER
			MAX-ACCESS	read-only
			STATUS	current
			::= { hmWanMbus00 91 }

hmWanMbus00VIF2B		OBJECT-TYPE
			SYNTAX	INTEGER
			MAX-ACCESS	read-only
			STATUS	current
			::= { hmWanMbus00 92 }

hmWanMbus00Value2B		OBJECT-TYPE
			SYNTAX	INTEGER
			MAX-ACCESS	read-only
			STATUS	current
			::= { hmWanMbus00 93 }

hmWanMbus00VIF2C		OBJECT-TYPE
			SYNTAX	INTEGER
			MAX-ACCESS	read-only
			STATUS	current
			::= { hmWanMbus00 94 }

hmWanMbus00Value2C		OBJECT-TYPE
			SYNTAX	INTEGER
			MAX-ACCESS	read-only
			STATUS	current
			::= { hmWanMbus00 95 }

hmWanMbus00VIF2D		OBJECT-TYPE
			SYNTAX	INTEGER
			MAX-ACCESS	read-only
			STATUS	current
			::= { hmWanMbus00 96 }

hmWanMbus00Value2D		OBJECT-TYPE
			SYNTAX	INTEGER
			MAX-ACCESS	read-only
			STATUS	current
			::= { hmWanMbus00 97 }

hmWanMbus00VIF2E		OBJECT-TYPE
			SYNTAX	INTEGER
			MAX-ACCESS	read-only
			STATUS	current
			::= { hmWanMbus00 98 }

hmWanMbus00Value2E		OBJECT-TYPE
			SYNTAX	INTEGER
			MAX-ACCESS	read-only
			STATUS	current
			::= { hmWanMbus00 99 }

hmWanMbus00VIF2F		OBJECT-TYPE
			SYNTAX	INTEGER
			MAX-ACCESS	read-only
			STATUS	current
			::= { hmWanMbus00 100 }

hmWanMbus00Value2F		OBJECT-TYPE
			SYNTAX	INTEGER
			MAX-ACCESS	read-only
			STATUS	current
			::= { hmWanMbus00 101 }

hmWanMbus01			OBJECT IDENTIFIER ::= { hmWanMbus 1 }

hmWanMbus01IdNumber		OBJECT-TYPE
			SYNTAX	Gauge32
			MAX-ACCESS	read-only
			STATUS	current
			::= { hmWanMbus01 1 }

hmWanMbus01Manufacturer	OBJECT-TYPE
			SYNTAX	Gauge32
			MAX-ACCESS	read-only
			STATUS	current
			::= { hmWanMbus01 2 }

hmWanMbus01Version		OBJECT-TYPE
			SYNTAX	Gauge32
			MAX-ACCESS	read-only
			STATUS	current
			::= { hmWanMbus01 3 }

hmWanMbus01Medium		OBJECT-TYPE
			SYNTAX	Gauge32
			MAX-ACCESS	read-only
			STATUS	current
			::= { hmWanMbus01 4 }

hmWanMbus01Status		OBJECT-TYPE
			SYNTAX	Gauge32
			MAX-ACCESS	read-only
			STATUS	current
			::= { hmWanMbus01 5 }

hmWanMbus01VIF00		OBJECT-TYPE
			SYNTAX	INTEGER
			MAX-ACCESS	read-only
			STATUS	current
			::= { hmWanMbus01 6 }

hmWanMbus01Value00		OBJECT-TYPE
			SYNTAX	INTEGER
			MAX-ACCESS	read-only
			STATUS	current
			::= { hmWanMbus01 7 }

hmWanMbus01VIF01		OBJECT-TYPE
			SYNTAX	INTEGER
			MAX-ACCESS	read-only
			STATUS	current
			::= { hmWanMbus01 8 }

hmWanMbus01Value01		OBJECT-TYPE
			SYNTAX	INTEGER
			MAX-ACCESS	read-only
			STATUS	current
			::= { hmWanMbus01 9 }

hmWanMbus01VIF02		OBJECT-TYPE
			SYNTAX	INTEGER
			MAX-ACCESS	read-only
			STATUS	current
			::= { hmWanMbus01 10 }

hmWanMbus01Value02		OBJECT-TYPE
			SYNTAX	INTEGER
			MAX-ACCESS	read-only
			STATUS	current
			::= { hmWanMbus01 11 }

hmWanMbus01VIF03		OBJECT-TYPE
			SYNTAX	INTEGER
			MAX-ACCESS	read-only
			STATUS	current
			::= { hmWanMbus01 12 }

hmWanMbus01Value03		OBJECT-TYPE
			SYNTAX	INTEGER
			MAX-ACCESS	read-only
			STATUS	current
			::= { hmWanMbus01 13 }

hmWanMbus01VIF04		OBJECT-TYPE
			SYNTAX	INTEGER
			MAX-ACCESS	read-only
			STATUS	current
			::= { hmWanMbus01 14 }

hmWanMbus01Value04		OBJECT-TYPE
			SYNTAX	INTEGER
			MAX-ACCESS	read-only
			STATUS	current
			::= { hmWanMbus01 15 }

hmWanMbus01VIF05		OBJECT-TYPE
			SYNTAX	INTEGER
			MAX-ACCESS	read-only
			STATUS	current
			::= { hmWanMbus01 16 }

hmWanMbus01Value05		OBJECT-TYPE
			SYNTAX	INTEGER
			MAX-ACCESS	read-only
			STATUS	current
			::= { hmWanMbus01 17 }

hmWanMbus01VIF06		OBJECT-TYPE
			SYNTAX	INTEGER
			MAX-ACCESS	read-only
			STATUS	current
			::= { hmWanMbus01 18 }

hmWanMbus01Value06		OBJECT-TYPE
			SYNTAX	INTEGER
			MAX-ACCESS	read-only
			STATUS	current
			::= { hmWanMbus01 19 }

hmWanMbus01VIF07		OBJECT-TYPE
			SYNTAX	INTEGER
			MAX-ACCESS	read-only
			STATUS	current
			::= { hmWanMbus01 20 }

hmWanMbus01Value07		OBJECT-TYPE
			SYNTAX	INTEGER
			MAX-ACCESS	read-only
			STATUS	current
			::= { hmWanMbus01 21 }

hmWanMbus01VIF08		OBJECT-TYPE
			SYNTAX	INTEGER
			MAX-ACCESS	read-only
			STATUS	current
			::= { hmWanMbus01 22 }

hmWanMbus01Value08		OBJECT-TYPE
			SYNTAX	INTEGER
			MAX-ACCESS	read-only
			STATUS	current
			::= { hmWanMbus01 23 }

hmWanMbus01VIF09		OBJECT-TYPE
			SYNTAX	INTEGER
			MAX-ACCESS	read-only
			STATUS	current
			::= { hmWanMbus01 24 }

hmWanMbus01Value09		OBJECT-TYPE
			SYNTAX	INTEGER
			MAX-ACCESS	read-only
			STATUS	current
			::= { hmWanMbus01 25 }

hmWanMbus01VIF0A		OBJECT-TYPE
			SYNTAX	INTEGER
			MAX-ACCESS	read-only
			STATUS	current
			::= { hmWanMbus01 26 }

hmWanMbus01Value0A		OBJECT-TYPE
			SYNTAX	INTEGER
			MAX-ACCESS	read-only
			STATUS	current
			::= { hmWanMbus01 27 }

hmWanMbus01VIF0B		OBJECT-TYPE
			SYNTAX	INTEGER
			MAX-ACCESS	read-only
			STATUS	current
			::= { hmWanMbus01 28 }

hmWanMbus01Value0B		OBJECT-TYPE
			SYNTAX	INTEGER
			MAX-ACCESS	read-only
			STATUS	current
			::= { hmWanMbus01 29 }

hmWanMbus01VIF0C		OBJECT-TYPE
			SYNTAX	INTEGER
			MAX-ACCESS	read-only
			STATUS	current
			::= { hmWanMbus01 30 }

hmWanMbus01Value0C		OBJECT-TYPE
			SYNTAX	INTEGER
			MAX-ACCESS	read-only
			STATUS	current
			::= { hmWanMbus01 31 }

hmWanMbus01VIF0D		OBJECT-TYPE
			SYNTAX	INTEGER
			MAX-ACCESS	read-only
			STATUS	current
			::= { hmWanMbus01 32 }

hmWanMbus01Value0D		OBJECT-TYPE
			SYNTAX	INTEGER
			MAX-ACCESS	read-only
			STATUS	current
			::= { hmWanMbus01 33 }

hmWanMbus01VIF0E		OBJECT-TYPE
			SYNTAX	INTEGER
			MAX-ACCESS	read-only
			STATUS	current
			::= { hmWanMbus01 34 }

hmWanMbus01Value0E		OBJECT-TYPE
			SYNTAX	INTEGER
			MAX-ACCESS	read-only
			STATUS	current
			::= { hmWanMbus01 35 }

hmWanMbus01VIF0F		OBJECT-TYPE
			SYNTAX	INTEGER
			MAX-ACCESS	read-only
			STATUS	current
			::= { hmWanMbus01 36 }

hmWanMbus01Value0F		OBJECT-TYPE
			SYNTAX	INTEGER
			MAX-ACCESS	read-only
			STATUS	current
			::= { hmWanMbus01 37 }

hmWanMbus01VIF10		OBJECT-TYPE
			SYNTAX	INTEGER
			MAX-ACCESS	read-only
			STATUS	current
			::= { hmWanMbus01 38 }

hmWanMbus01Value10		OBJECT-TYPE
			SYNTAX	INTEGER
			MAX-ACCESS	read-only
			STATUS	current
			::= { hmWanMbus01 39 }

hmWanMbus01VIF11		OBJECT-TYPE
			SYNTAX	INTEGER
			MAX-ACCESS	read-only
			STATUS	current
			::= { hmWanMbus01 40 }

hmWanMbus01Value11		OBJECT-TYPE
			SYNTAX	INTEGER
			MAX-ACCESS	read-only
			STATUS	current
			::= { hmWanMbus01 41 }

hmWanMbus01VIF12		OBJECT-TYPE
			SYNTAX	INTEGER
			MAX-ACCESS	read-only
			STATUS	current
			::= { hmWanMbus01 42 }

hmWanMbus01Value12		OBJECT-TYPE
			SYNTAX	INTEGER
			MAX-ACCESS	read-only
			STATUS	current
			::= { hmWanMbus01 43 }

hmWanMbus01VIF13		OBJECT-TYPE
			SYNTAX	INTEGER
			MAX-ACCESS	read-only
			STATUS	current
			::= { hmWanMbus01 44 }

hmWanMbus01Value13		OBJECT-TYPE
			SYNTAX	INTEGER
			MAX-ACCESS	read-only
			STATUS	current
			::= { hmWanMbus01 45 }

hmWanMbus01VIF14		OBJECT-TYPE
			SYNTAX	INTEGER
			MAX-ACCESS	read-only
			STATUS	current
			::= { hmWanMbus01 46 }

hmWanMbus01Value14		OBJECT-TYPE
			SYNTAX	INTEGER
			MAX-ACCESS	read-only
			STATUS	current
			::= { hmWanMbus01 47 }

hmWanMbus01VIF15		OBJECT-TYPE
			SYNTAX	INTEGER
			MAX-ACCESS	read-only
			STATUS	current
			::= { hmWanMbus01 48 }

hmWanMbus01Value15		OBJECT-TYPE
			SYNTAX	INTEGER
			MAX-ACCESS	read-only
			STATUS	current
			::= { hmWanMbus01 49 }

hmWanMbus01VIF16		OBJECT-TYPE
			SYNTAX	INTEGER
			MAX-ACCESS	read-only
			STATUS	current
			::= { hmWanMbus01 50 }

hmWanMbus01Value16		OBJECT-TYPE
			SYNTAX	INTEGER
			MAX-ACCESS	read-only
			STATUS	current
			::= { hmWanMbus01 51 }

hmWanMbus01VIF17		OBJECT-TYPE
			SYNTAX	INTEGER
			MAX-ACCESS	read-only
			STATUS	current
			::= { hmWanMbus01 52 }

hmWanMbus01Value17		OBJECT-TYPE
			SYNTAX	INTEGER
			MAX-ACCESS	read-only
			STATUS	current
			::= { hmWanMbus01 53 }

hmWanMbus01VIF18		OBJECT-TYPE
			SYNTAX	INTEGER
			MAX-ACCESS	read-only
			STATUS	current
			::= { hmWanMbus01 54 }

hmWanMbus01Value18		OBJECT-TYPE
			SYNTAX	INTEGER
			MAX-ACCESS	read-only
			STATUS	current
			::= { hmWanMbus01 55 }

hmWanMbus01VIF19		OBJECT-TYPE
			SYNTAX	INTEGER
			MAX-ACCESS	read-only
			STATUS	current
			::= { hmWanMbus01 56 }

hmWanMbus01Value19		OBJECT-TYPE
			SYNTAX	INTEGER
			MAX-ACCESS	read-only
			STATUS	current
			::= { hmWanMbus01 57 }

hmWanMbus01VIF1A		OBJECT-TYPE
			SYNTAX	INTEGER
			MAX-ACCESS	read-only
			STATUS	current
			::= { hmWanMbus01 58 }

hmWanMbus01Value1A		OBJECT-TYPE
			SYNTAX	INTEGER
			MAX-ACCESS	read-only
			STATUS	current
			::= { hmWanMbus01 59 }

hmWanMbus01VIF1B		OBJECT-TYPE
			SYNTAX	INTEGER
			MAX-ACCESS	read-only
			STATUS	current
			::= { hmWanMbus01 60 }

hmWanMbus01Value1B		OBJECT-TYPE
			SYNTAX	INTEGER
			MAX-ACCESS	read-only
			STATUS	current
			::= { hmWanMbus01 61 }

hmWanMbus01VIF1C		OBJECT-TYPE
			SYNTAX	INTEGER
			MAX-ACCESS	read-only
			STATUS	current
			::= { hmWanMbus01 62 }

hmWanMbus01Value1C		OBJECT-TYPE
			SYNTAX	INTEGER
			MAX-ACCESS	read-only
			STATUS	current
			::= { hmWanMbus01 63 }

hmWanMbus01VIF1D		OBJECT-TYPE
			SYNTAX	INTEGER
			MAX-ACCESS	read-only
			STATUS	current
			::= { hmWanMbus01 64 }

hmWanMbus01Value1D		OBJECT-TYPE
			SYNTAX	INTEGER
			MAX-ACCESS	read-only
			STATUS	current
			::= { hmWanMbus01 65 }

hmWanMbus01VIF1E		OBJECT-TYPE
			SYNTAX	INTEGER
			MAX-ACCESS	read-only
			STATUS	current
			::= { hmWanMbus01 66 }

hmWanMbus01Value1E		OBJECT-TYPE
			SYNTAX	INTEGER
			MAX-ACCESS	read-only
			STATUS	current
			::= { hmWanMbus01 67 }

hmWanMbus01VIF1F		OBJECT-TYPE
			SYNTAX	INTEGER
			MAX-ACCESS	read-only
			STATUS	current
			::= { hmWanMbus01 68 }

hmWanMbus01Value1F		OBJECT-TYPE
			SYNTAX	INTEGER
			MAX-ACCESS	read-only
			STATUS	current
			::= { hmWanMbus01 69 }

hmWanMbus01VIF20		OBJECT-TYPE
			SYNTAX	INTEGER
			MAX-ACCESS	read-only
			STATUS	current
			::= { hmWanMbus01 70 }

hmWanMbus01Value20		OBJECT-TYPE
			SYNTAX	INTEGER
			MAX-ACCESS	read-only
			STATUS	current
			::= { hmWanMbus01 71 }

hmWanMbus01VIF21		OBJECT-TYPE
			SYNTAX	INTEGER
			MAX-ACCESS	read-only
			STATUS	current
			::= { hmWanMbus01 72 }

hmWanMbus01Value21		OBJECT-TYPE
			SYNTAX	INTEGER
			MAX-ACCESS	read-only
			STATUS	current
			::= { hmWanMbus01 73 }

hmWanMbus01VIF22		OBJECT-TYPE
			SYNTAX	INTEGER
			MAX-ACCESS	read-only
			STATUS	current
			::= { hmWanMbus01 74 }

hmWanMbus01Value22		OBJECT-TYPE
			SYNTAX	INTEGER
			MAX-ACCESS	read-only
			STATUS	current
			::= { hmWanMbus01 75 }

hmWanMbus01VIF23		OBJECT-TYPE
			SYNTAX	INTEGER
			MAX-ACCESS	read-only
			STATUS	current
			::= { hmWanMbus01 76 }

hmWanMbus01Value23		OBJECT-TYPE
			SYNTAX	INTEGER
			MAX-ACCESS	read-only
			STATUS	current
			::= { hmWanMbus01 77 }

hmWanMbus01VIF24		OBJECT-TYPE
			SYNTAX	INTEGER
			MAX-ACCESS	read-only
			STATUS	current
			::= { hmWanMbus01 78 }

hmWanMbus01Value24		OBJECT-TYPE
			SYNTAX	INTEGER
			MAX-ACCESS	read-only
			STATUS	current
			::= { hmWanMbus01 79 }

hmWanMbus01VIF25		OBJECT-TYPE
			SYNTAX	INTEGER
			MAX-ACCESS	read-only
			STATUS	current
			::= { hmWanMbus01 80 }

hmWanMbus01Value25		OBJECT-TYPE
			SYNTAX	INTEGER
			MAX-ACCESS	read-only
			STATUS	current
			::= { hmWanMbus01 81 }

hmWanMbus01VIF26		OBJECT-TYPE
			SYNTAX	INTEGER
			MAX-ACCESS	read-only
			STATUS	current
			::= { hmWanMbus01 82 }

hmWanMbus01Value26		OBJECT-TYPE
			SYNTAX	INTEGER
			MAX-ACCESS	read-only
			STATUS	current
			::= { hmWanMbus01 83 }

hmWanMbus01VIF27		OBJECT-TYPE
			SYNTAX	INTEGER
			MAX-ACCESS	read-only
			STATUS	current
			::= { hmWanMbus01 84 }

hmWanMbus01Value27		OBJECT-TYPE
			SYNTAX	INTEGER
			MAX-ACCESS	read-only
			STATUS	current
			::= { hmWanMbus01 85 }

hmWanMbus01VIF28		OBJECT-TYPE
			SYNTAX	INTEGER
			MAX-ACCESS	read-only
			STATUS	current
			::= { hmWanMbus01 86 }

hmWanMbus01Value28		OBJECT-TYPE
			SYNTAX	INTEGER
			MAX-ACCESS	read-only
			STATUS	current
			::= { hmWanMbus01 87 }

hmWanMbus01VIF29		OBJECT-TYPE
			SYNTAX	INTEGER
			MAX-ACCESS	read-only
			STATUS	current
			::= { hmWanMbus01 88 }

hmWanMbus01Value29		OBJECT-TYPE
			SYNTAX	INTEGER
			MAX-ACCESS	read-only
			STATUS	current
			::= { hmWanMbus01 89 }

hmWanMbus01VIF2A		OBJECT-TYPE
			SYNTAX	INTEGER
			MAX-ACCESS	read-only
			STATUS	current
			::= { hmWanMbus01 90 }

hmWanMbus01Value2A		OBJECT-TYPE
			SYNTAX	INTEGER
			MAX-ACCESS	read-only
			STATUS	current
			::= { hmWanMbus01 91 }

hmWanMbus01VIF2B		OBJECT-TYPE
			SYNTAX	INTEGER
			MAX-ACCESS	read-only
			STATUS	current
			::= { hmWanMbus01 92 }

hmWanMbus01Value2B		OBJECT-TYPE
			SYNTAX	INTEGER
			MAX-ACCESS	read-only
			STATUS	current
			::= { hmWanMbus01 93 }

hmWanMbus01VIF2C		OBJECT-TYPE
			SYNTAX	INTEGER
			MAX-ACCESS	read-only
			STATUS	current
			::= { hmWanMbus01 94 }

hmWanMbus01Value2C		OBJECT-TYPE
			SYNTAX	INTEGER
			MAX-ACCESS	read-only
			STATUS	current
			::= { hmWanMbus01 95 }

hmWanMbus01VIF2D		OBJECT-TYPE
			SYNTAX	INTEGER
			MAX-ACCESS	read-only
			STATUS	current
			::= { hmWanMbus01 96 }

hmWanMbus01Value2D		OBJECT-TYPE
			SYNTAX	INTEGER
			MAX-ACCESS	read-only
			STATUS	current
			::= { hmWanMbus01 97 }

hmWanMbus01VIF2E		OBJECT-TYPE
			SYNTAX	INTEGER
			MAX-ACCESS	read-only
			STATUS	current
			::= { hmWanMbus01 98 }

hmWanMbus01Value2E		OBJECT-TYPE
			SYNTAX	INTEGER
			MAX-ACCESS	read-only
			STATUS	current
			::= { hmWanMbus01 99 }

hmWanMbus01VIF2F		OBJECT-TYPE
			SYNTAX	INTEGER
			MAX-ACCESS	read-only
			STATUS	current
			::= { hmWanMbus01 100 }

hmWanMbus01Value2F		OBJECT-TYPE
			SYNTAX	INTEGER
			MAX-ACCESS	read-only
			STATUS	current
			::= { hmWanMbus01 101 }

hmWanMbus02			OBJECT IDENTIFIER ::= { hmWanMbus 2 }

hmWanMbus02IdNumber		OBJECT-TYPE
			SYNTAX	Gauge32
			MAX-ACCESS	read-only
			STATUS	current
			::= { hmWanMbus02 1 }

hmWanMbus02Manufacturer	OBJECT-TYPE
			SYNTAX	Gauge32
			MAX-ACCESS	read-only
			STATUS	current
			::= { hmWanMbus02 2 }

hmWanMbus02Version		OBJECT-TYPE
			SYNTAX	Gauge32
			MAX-ACCESS	read-only
			STATUS	current
			::= { hmWanMbus02 3 }

hmWanMbus02Medium		OBJECT-TYPE
			SYNTAX	Gauge32
			MAX-ACCESS	read-only
			STATUS	current
			::= { hmWanMbus02 4 }

hmWanMbus02Status		OBJECT-TYPE
			SYNTAX	Gauge32
			MAX-ACCESS	read-only
			STATUS	current
			::= { hmWanMbus02 5 }

hmWanMbus02VIF00		OBJECT-TYPE
			SYNTAX	INTEGER
			MAX-ACCESS	read-only
			STATUS	current
			::= { hmWanMbus02 6 }

hmWanMbus02Value00		OBJECT-TYPE
			SYNTAX	INTEGER
			MAX-ACCESS	read-only
			STATUS	current
			::= { hmWanMbus02 7 }

hmWanMbus02VIF01		OBJECT-TYPE
			SYNTAX	INTEGER
			MAX-ACCESS	read-only
			STATUS	current
			::= { hmWanMbus02 8 }

hmWanMbus02Value01		OBJECT-TYPE
			SYNTAX	INTEGER
			MAX-ACCESS	read-only
			STATUS	current
			::= { hmWanMbus02 9 }

hmWanMbus02VIF02		OBJECT-TYPE
			SYNTAX	INTEGER
			MAX-ACCESS	read-only
			STATUS	current
			::= { hmWanMbus02 10 }

hmWanMbus02Value02		OBJECT-TYPE
			SYNTAX	INTEGER
			MAX-ACCESS	read-only
			STATUS	current
			::= { hmWanMbus02 11 }

hmWanMbus02VIF03		OBJECT-TYPE
			SYNTAX	INTEGER
			MAX-ACCESS	read-only
			STATUS	current
			::= { hmWanMbus02 12 }

hmWanMbus02Value03		OBJECT-TYPE
			SYNTAX	INTEGER
			MAX-ACCESS	read-only
			STATUS	current
			::= { hmWanMbus02 13 }

hmWanMbus02VIF04		OBJECT-TYPE
			SYNTAX	INTEGER
			MAX-ACCESS	read-only
			STATUS	current
			::= { hmWanMbus02 14 }

hmWanMbus02Value04		OBJECT-TYPE
			SYNTAX	INTEGER
			MAX-ACCESS	read-only
			STATUS	current
			::= { hmWanMbus02 15 }

hmWanMbus02VIF05		OBJECT-TYPE
			SYNTAX	INTEGER
			MAX-ACCESS	read-only
			STATUS	current
			::= { hmWanMbus02 16 }

hmWanMbus02Value05		OBJECT-TYPE
			SYNTAX	INTEGER
			MAX-ACCESS	read-only
			STATUS	current
			::= { hmWanMbus02 17 }

hmWanMbus02VIF06		OBJECT-TYPE
			SYNTAX	INTEGER
			MAX-ACCESS	read-only
			STATUS	current
			::= { hmWanMbus02 18 }

hmWanMbus02Value06		OBJECT-TYPE
			SYNTAX	INTEGER
			MAX-ACCESS	read-only
			STATUS	current
			::= { hmWanMbus02 19 }

hmWanMbus02VIF07		OBJECT-TYPE
			SYNTAX	INTEGER
			MAX-ACCESS	read-only
			STATUS	current
			::= { hmWanMbus02 20 }

hmWanMbus02Value07		OBJECT-TYPE
			SYNTAX	INTEGER
			MAX-ACCESS	read-only
			STATUS	current
			::= { hmWanMbus02 21 }

hmWanMbus02VIF08		OBJECT-TYPE
			SYNTAX	INTEGER
			MAX-ACCESS	read-only
			STATUS	current
			::= { hmWanMbus02 22 }

hmWanMbus02Value08		OBJECT-TYPE
			SYNTAX	INTEGER
			MAX-ACCESS	read-only
			STATUS	current
			::= { hmWanMbus02 23 }

hmWanMbus02VIF09		OBJECT-TYPE
			SYNTAX	INTEGER
			MAX-ACCESS	read-only
			STATUS	current
			::= { hmWanMbus02 24 }

hmWanMbus02Value09		OBJECT-TYPE
			SYNTAX	INTEGER
			MAX-ACCESS	read-only
			STATUS	current
			::= { hmWanMbus02 25 }

hmWanMbus02VIF0A		OBJECT-TYPE
			SYNTAX	INTEGER
			MAX-ACCESS	read-only
			STATUS	current
			::= { hmWanMbus02 26 }

hmWanMbus02Value0A		OBJECT-TYPE
			SYNTAX	INTEGER
			MAX-ACCESS	read-only
			STATUS	current
			::= { hmWanMbus02 27 }

hmWanMbus02VIF0B		OBJECT-TYPE
			SYNTAX	INTEGER
			MAX-ACCESS	read-only
			STATUS	current
			::= { hmWanMbus02 28 }

hmWanMbus02Value0B		OBJECT-TYPE
			SYNTAX	INTEGER
			MAX-ACCESS	read-only
			STATUS	current
			::= { hmWanMbus02 29 }

hmWanMbus02VIF0C		OBJECT-TYPE
			SYNTAX	INTEGER
			MAX-ACCESS	read-only
			STATUS	current
			::= { hmWanMbus02 30 }

hmWanMbus02Value0C		OBJECT-TYPE
			SYNTAX	INTEGER
			MAX-ACCESS	read-only
			STATUS	current
			::= { hmWanMbus02 31 }

hmWanMbus02VIF0D		OBJECT-TYPE
			SYNTAX	INTEGER
			MAX-ACCESS	read-only
			STATUS	current
			::= { hmWanMbus02 32 }

hmWanMbus02Value0D		OBJECT-TYPE
			SYNTAX	INTEGER
			MAX-ACCESS	read-only
			STATUS	current
			::= { hmWanMbus02 33 }

hmWanMbus02VIF0E		OBJECT-TYPE
			SYNTAX	INTEGER
			MAX-ACCESS	read-only
			STATUS	current
			::= { hmWanMbus02 34 }

hmWanMbus02Value0E		OBJECT-TYPE
			SYNTAX	INTEGER
			MAX-ACCESS	read-only
			STATUS	current
			::= { hmWanMbus02 35 }

hmWanMbus02VIF0F		OBJECT-TYPE
			SYNTAX	INTEGER
			MAX-ACCESS	read-only
			STATUS	current
			::= { hmWanMbus02 36 }

hmWanMbus02Value0F		OBJECT-TYPE
			SYNTAX	INTEGER
			MAX-ACCESS	read-only
			STATUS	current
			::= { hmWanMbus02 37 }

hmWanMbus02VIF10		OBJECT-TYPE
			SYNTAX	INTEGER
			MAX-ACCESS	read-only
			STATUS	current
			::= { hmWanMbus02 38 }

hmWanMbus02Value10		OBJECT-TYPE
			SYNTAX	INTEGER
			MAX-ACCESS	read-only
			STATUS	current
			::= { hmWanMbus02 39 }

hmWanMbus02VIF11		OBJECT-TYPE
			SYNTAX	INTEGER
			MAX-ACCESS	read-only
			STATUS	current
			::= { hmWanMbus02 40 }

hmWanMbus02Value11		OBJECT-TYPE
			SYNTAX	INTEGER
			MAX-ACCESS	read-only
			STATUS	current
			::= { hmWanMbus02 41 }

hmWanMbus02VIF12		OBJECT-TYPE
			SYNTAX	INTEGER
			MAX-ACCESS	read-only
			STATUS	current
			::= { hmWanMbus02 42 }

hmWanMbus02Value12		OBJECT-TYPE
			SYNTAX	INTEGER
			MAX-ACCESS	read-only
			STATUS	current
			::= { hmWanMbus02 43 }

hmWanMbus02VIF13		OBJECT-TYPE
			SYNTAX	INTEGER
			MAX-ACCESS	read-only
			STATUS	current
			::= { hmWanMbus02 44 }

hmWanMbus02Value13		OBJECT-TYPE
			SYNTAX	INTEGER
			MAX-ACCESS	read-only
			STATUS	current
			::= { hmWanMbus02 45 }

hmWanMbus02VIF14		OBJECT-TYPE
			SYNTAX	INTEGER
			MAX-ACCESS	read-only
			STATUS	current
			::= { hmWanMbus02 46 }

hmWanMbus02Value14		OBJECT-TYPE
			SYNTAX	INTEGER
			MAX-ACCESS	read-only
			STATUS	current
			::= { hmWanMbus02 47 }

hmWanMbus02VIF15		OBJECT-TYPE
			SYNTAX	INTEGER
			MAX-ACCESS	read-only
			STATUS	current
			::= { hmWanMbus02 48 }

hmWanMbus02Value15		OBJECT-TYPE
			SYNTAX	INTEGER
			MAX-ACCESS	read-only
			STATUS	current
			::= { hmWanMbus02 49 }

hmWanMbus02VIF16		OBJECT-TYPE
			SYNTAX	INTEGER
			MAX-ACCESS	read-only
			STATUS	current
			::= { hmWanMbus02 50 }

hmWanMbus02Value16		OBJECT-TYPE
			SYNTAX	INTEGER
			MAX-ACCESS	read-only
			STATUS	current
			::= { hmWanMbus02 51 }

hmWanMbus02VIF17		OBJECT-TYPE
			SYNTAX	INTEGER
			MAX-ACCESS	read-only
			STATUS	current
			::= { hmWanMbus02 52 }

hmWanMbus02Value17		OBJECT-TYPE
			SYNTAX	INTEGER
			MAX-ACCESS	read-only
			STATUS	current
			::= { hmWanMbus02 53 }

hmWanMbus02VIF18		OBJECT-TYPE
			SYNTAX	INTEGER
			MAX-ACCESS	read-only
			STATUS	current
			::= { hmWanMbus02 54 }

hmWanMbus02Value18		OBJECT-TYPE
			SYNTAX	INTEGER
			MAX-ACCESS	read-only
			STATUS	current
			::= { hmWanMbus02 55 }

hmWanMbus02VIF19		OBJECT-TYPE
			SYNTAX	INTEGER
			MAX-ACCESS	read-only
			STATUS	current
			::= { hmWanMbus02 56 }

hmWanMbus02Value19		OBJECT-TYPE
			SYNTAX	INTEGER
			MAX-ACCESS	read-only
			STATUS	current
			::= { hmWanMbus02 57 }

hmWanMbus02VIF1A		OBJECT-TYPE
			SYNTAX	INTEGER
			MAX-ACCESS	read-only
			STATUS	current
			::= { hmWanMbus02 58 }

hmWanMbus02Value1A		OBJECT-TYPE
			SYNTAX	INTEGER
			MAX-ACCESS	read-only
			STATUS	current
			::= { hmWanMbus02 59 }

hmWanMbus02VIF1B		OBJECT-TYPE
			SYNTAX	INTEGER
			MAX-ACCESS	read-only
			STATUS	current
			::= { hmWanMbus02 60 }

hmWanMbus02Value1B		OBJECT-TYPE
			SYNTAX	INTEGER
			MAX-ACCESS	read-only
			STATUS	current
			::= { hmWanMbus02 61 }

hmWanMbus02VIF1C		OBJECT-TYPE
			SYNTAX	INTEGER
			MAX-ACCESS	read-only
			STATUS	current
			::= { hmWanMbus02 62 }

hmWanMbus02Value1C		OBJECT-TYPE
			SYNTAX	INTEGER
			MAX-ACCESS	read-only
			STATUS	current
			::= { hmWanMbus02 63 }

hmWanMbus02VIF1D		OBJECT-TYPE
			SYNTAX	INTEGER
			MAX-ACCESS	read-only
			STATUS	current
			::= { hmWanMbus02 64 }

hmWanMbus02Value1D		OBJECT-TYPE
			SYNTAX	INTEGER
			MAX-ACCESS	read-only
			STATUS	current
			::= { hmWanMbus02 65 }

hmWanMbus02VIF1E		OBJECT-TYPE
			SYNTAX	INTEGER
			MAX-ACCESS	read-only
			STATUS	current
			::= { hmWanMbus02 66 }

hmWanMbus02Value1E		OBJECT-TYPE
			SYNTAX	INTEGER
			MAX-ACCESS	read-only
			STATUS	current
			::= { hmWanMbus02 67 }

hmWanMbus02VIF1F		OBJECT-TYPE
			SYNTAX	INTEGER
			MAX-ACCESS	read-only
			STATUS	current
			::= { hmWanMbus02 68 }

hmWanMbus02Value1F		OBJECT-TYPE
			SYNTAX	INTEGER
			MAX-ACCESS	read-only
			STATUS	current
			::= { hmWanMbus02 69 }

hmWanMbus02VIF20		OBJECT-TYPE
			SYNTAX	INTEGER
			MAX-ACCESS	read-only
			STATUS	current
			::= { hmWanMbus02 70 }

hmWanMbus02Value20		OBJECT-TYPE
			SYNTAX	INTEGER
			MAX-ACCESS	read-only
			STATUS	current
			::= { hmWanMbus02 71 }

hmWanMbus02VIF21		OBJECT-TYPE
			SYNTAX	INTEGER
			MAX-ACCESS	read-only
			STATUS	current
			::= { hmWanMbus02 72 }

hmWanMbus02Value21		OBJECT-TYPE
			SYNTAX	INTEGER
			MAX-ACCESS	read-only
			STATUS	current
			::= { hmWanMbus02 73 }

hmWanMbus02VIF22		OBJECT-TYPE
			SYNTAX	INTEGER
			MAX-ACCESS	read-only
			STATUS	current
			::= { hmWanMbus02 74 }

hmWanMbus02Value22		OBJECT-TYPE
			SYNTAX	INTEGER
			MAX-ACCESS	read-only
			STATUS	current
			::= { hmWanMbus02 75 }

hmWanMbus02VIF23		OBJECT-TYPE
			SYNTAX	INTEGER
			MAX-ACCESS	read-only
			STATUS	current
			::= { hmWanMbus02 76 }

hmWanMbus02Value23		OBJECT-TYPE
			SYNTAX	INTEGER
			MAX-ACCESS	read-only
			STATUS	current
			::= { hmWanMbus02 77 }

hmWanMbus02VIF24		OBJECT-TYPE
			SYNTAX	INTEGER
			MAX-ACCESS	read-only
			STATUS	current
			::= { hmWanMbus02 78 }

hmWanMbus02Value24		OBJECT-TYPE
			SYNTAX	INTEGER
			MAX-ACCESS	read-only
			STATUS	current
			::= { hmWanMbus02 79 }

hmWanMbus02VIF25		OBJECT-TYPE
			SYNTAX	INTEGER
			MAX-ACCESS	read-only
			STATUS	current
			::= { hmWanMbus02 80 }

hmWanMbus02Value25		OBJECT-TYPE
			SYNTAX	INTEGER
			MAX-ACCESS	read-only
			STATUS	current
			::= { hmWanMbus02 81 }

hmWanMbus02VIF26		OBJECT-TYPE
			SYNTAX	INTEGER
			MAX-ACCESS	read-only
			STATUS	current
			::= { hmWanMbus02 82 }

hmWanMbus02Value26		OBJECT-TYPE
			SYNTAX	INTEGER
			MAX-ACCESS	read-only
			STATUS	current
			::= { hmWanMbus02 83 }

hmWanMbus02VIF27		OBJECT-TYPE
			SYNTAX	INTEGER
			MAX-ACCESS	read-only
			STATUS	current
			::= { hmWanMbus02 84 }

hmWanMbus02Value27		OBJECT-TYPE
			SYNTAX	INTEGER
			MAX-ACCESS	read-only
			STATUS	current
			::= { hmWanMbus02 85 }

hmWanMbus02VIF28		OBJECT-TYPE
			SYNTAX	INTEGER
			MAX-ACCESS	read-only
			STATUS	current
			::= { hmWanMbus02 86 }

hmWanMbus02Value28		OBJECT-TYPE
			SYNTAX	INTEGER
			MAX-ACCESS	read-only
			STATUS	current
			::= { hmWanMbus02 87 }

hmWanMbus02VIF29		OBJECT-TYPE
			SYNTAX	INTEGER
			MAX-ACCESS	read-only
			STATUS	current
			::= { hmWanMbus02 88 }

hmWanMbus02Value29		OBJECT-TYPE
			SYNTAX	INTEGER
			MAX-ACCESS	read-only
			STATUS	current
			::= { hmWanMbus02 89 }

hmWanMbus02VIF2A		OBJECT-TYPE
			SYNTAX	INTEGER
			MAX-ACCESS	read-only
			STATUS	current
			::= { hmWanMbus02 90 }

hmWanMbus02Value2A		OBJECT-TYPE
			SYNTAX	INTEGER
			MAX-ACCESS	read-only
			STATUS	current
			::= { hmWanMbus02 91 }

hmWanMbus02VIF2B		OBJECT-TYPE
			SYNTAX	INTEGER
			MAX-ACCESS	read-only
			STATUS	current
			::= { hmWanMbus02 92 }

hmWanMbus02Value2B		OBJECT-TYPE
			SYNTAX	INTEGER
			MAX-ACCESS	read-only
			STATUS	current
			::= { hmWanMbus02 93 }

hmWanMbus02VIF2C		OBJECT-TYPE
			SYNTAX	INTEGER
			MAX-ACCESS	read-only
			STATUS	current
			::= { hmWanMbus02 94 }

hmWanMbus02Value2C		OBJECT-TYPE
			SYNTAX	INTEGER
			MAX-ACCESS	read-only
			STATUS	current
			::= { hmWanMbus02 95 }

hmWanMbus02VIF2D		OBJECT-TYPE
			SYNTAX	INTEGER
			MAX-ACCESS	read-only
			STATUS	current
			::= { hmWanMbus02 96 }

hmWanMbus02Value2D		OBJECT-TYPE
			SYNTAX	INTEGER
			MAX-ACCESS	read-only
			STATUS	current
			::= { hmWanMbus02 97 }

hmWanMbus02VIF2E		OBJECT-TYPE
			SYNTAX	INTEGER
			MAX-ACCESS	read-only
			STATUS	current
			::= { hmWanMbus02 98 }

hmWanMbus02Value2E		OBJECT-TYPE
			SYNTAX	INTEGER
			MAX-ACCESS	read-only
			STATUS	current
			::= { hmWanMbus02 99 }

hmWanMbus02VIF2F		OBJECT-TYPE
			SYNTAX	INTEGER
			MAX-ACCESS	read-only
			STATUS	current
			::= { hmWanMbus02 100 }

hmWanMbus02Value2F		OBJECT-TYPE
			SYNTAX	INTEGER
			MAX-ACCESS	read-only
			STATUS	current
			::= { hmWanMbus02 101 }

hmWanMbus03			OBJECT IDENTIFIER ::= { hmWanMbus 3 }

hmWanMbus03IdNumber		OBJECT-TYPE
			SYNTAX	Gauge32
			MAX-ACCESS	read-only
			STATUS	current
			::= { hmWanMbus03 1 }

hmWanMbus03Manufacturer	OBJECT-TYPE
			SYNTAX	Gauge32
			MAX-ACCESS	read-only
			STATUS	current
			::= { hmWanMbus03 2 }

hmWanMbus03Version		OBJECT-TYPE
			SYNTAX	Gauge32
			MAX-ACCESS	read-only
			STATUS	current
			::= { hmWanMbus03 3 }

hmWanMbus03Medium		OBJECT-TYPE
			SYNTAX	Gauge32
			MAX-ACCESS	read-only
			STATUS	current
			::= { hmWanMbus03 4 }

hmWanMbus03Status		OBJECT-TYPE
			SYNTAX	Gauge32
			MAX-ACCESS	read-only
			STATUS	current
			::= { hmWanMbus03 5 }

hmWanMbus03VIF00		OBJECT-TYPE
			SYNTAX	INTEGER
			MAX-ACCESS	read-only
			STATUS	current
			::= { hmWanMbus03 6 }

hmWanMbus03Value00		OBJECT-TYPE
			SYNTAX	INTEGER
			MAX-ACCESS	read-only
			STATUS	current
			::= { hmWanMbus03 7 }

hmWanMbus03VIF01		OBJECT-TYPE
			SYNTAX	INTEGER
			MAX-ACCESS	read-only
			STATUS	current
			::= { hmWanMbus03 8 }

hmWanMbus03Value01		OBJECT-TYPE
			SYNTAX	INTEGER
			MAX-ACCESS	read-only
			STATUS	current
			::= { hmWanMbus03 9 }

hmWanMbus03VIF02		OBJECT-TYPE
			SYNTAX	INTEGER
			MAX-ACCESS	read-only
			STATUS	current
			::= { hmWanMbus03 10 }

hmWanMbus03Value02		OBJECT-TYPE
			SYNTAX	INTEGER
			MAX-ACCESS	read-only
			STATUS	current
			::= { hmWanMbus03 11 }

hmWanMbus03VIF03		OBJECT-TYPE
			SYNTAX	INTEGER
			MAX-ACCESS	read-only
			STATUS	current
			::= { hmWanMbus03 12 }

hmWanMbus03Value03		OBJECT-TYPE
			SYNTAX	INTEGER
			MAX-ACCESS	read-only
			STATUS	current
			::= { hmWanMbus03 13 }

hmWanMbus03VIF04		OBJECT-TYPE
			SYNTAX	INTEGER
			MAX-ACCESS	read-only
			STATUS	current
			::= { hmWanMbus03 14 }

hmWanMbus03Value04		OBJECT-TYPE
			SYNTAX	INTEGER
			MAX-ACCESS	read-only
			STATUS	current
			::= { hmWanMbus03 15 }

hmWanMbus03VIF05		OBJECT-TYPE
			SYNTAX	INTEGER
			MAX-ACCESS	read-only
			STATUS	current
			::= { hmWanMbus03 16 }

hmWanMbus03Value05		OBJECT-TYPE
			SYNTAX	INTEGER
			MAX-ACCESS	read-only
			STATUS	current
			::= { hmWanMbus03 17 }

hmWanMbus03VIF06		OBJECT-TYPE
			SYNTAX	INTEGER
			MAX-ACCESS	read-only
			STATUS	current
			::= { hmWanMbus03 18 }

hmWanMbus03Value06		OBJECT-TYPE
			SYNTAX	INTEGER
			MAX-ACCESS	read-only
			STATUS	current
			::= { hmWanMbus03 19 }

hmWanMbus03VIF07		OBJECT-TYPE
			SYNTAX	INTEGER
			MAX-ACCESS	read-only
			STATUS	current
			::= { hmWanMbus03 20 }

hmWanMbus03Value07		OBJECT-TYPE
			SYNTAX	INTEGER
			MAX-ACCESS	read-only
			STATUS	current
			::= { hmWanMbus03 21 }

hmWanMbus03VIF08		OBJECT-TYPE
			SYNTAX	INTEGER
			MAX-ACCESS	read-only
			STATUS	current
			::= { hmWanMbus03 22 }

hmWanMbus03Value08		OBJECT-TYPE
			SYNTAX	INTEGER
			MAX-ACCESS	read-only
			STATUS	current
			::= { hmWanMbus03 23 }

hmWanMbus03VIF09		OBJECT-TYPE
			SYNTAX	INTEGER
			MAX-ACCESS	read-only
			STATUS	current
			::= { hmWanMbus03 24 }

hmWanMbus03Value09		OBJECT-TYPE
			SYNTAX	INTEGER
			MAX-ACCESS	read-only
			STATUS	current
			::= { hmWanMbus03 25 }

hmWanMbus03VIF0A		OBJECT-TYPE
			SYNTAX	INTEGER
			MAX-ACCESS	read-only
			STATUS	current
			::= { hmWanMbus03 26 }

hmWanMbus03Value0A		OBJECT-TYPE
			SYNTAX	INTEGER
			MAX-ACCESS	read-only
			STATUS	current
			::= { hmWanMbus03 27 }

hmWanMbus03VIF0B		OBJECT-TYPE
			SYNTAX	INTEGER
			MAX-ACCESS	read-only
			STATUS	current
			::= { hmWanMbus03 28 }

hmWanMbus03Value0B		OBJECT-TYPE
			SYNTAX	INTEGER
			MAX-ACCESS	read-only
			STATUS	current
			::= { hmWanMbus03 29 }

hmWanMbus03VIF0C		OBJECT-TYPE
			SYNTAX	INTEGER
			MAX-ACCESS	read-only
			STATUS	current
			::= { hmWanMbus03 30 }

hmWanMbus03Value0C		OBJECT-TYPE
			SYNTAX	INTEGER
			MAX-ACCESS	read-only
			STATUS	current
			::= { hmWanMbus03 31 }

hmWanMbus03VIF0D		OBJECT-TYPE
			SYNTAX	INTEGER
			MAX-ACCESS	read-only
			STATUS	current
			::= { hmWanMbus03 32 }

hmWanMbus03Value0D		OBJECT-TYPE
			SYNTAX	INTEGER
			MAX-ACCESS	read-only
			STATUS	current
			::= { hmWanMbus03 33 }

hmWanMbus03VIF0E		OBJECT-TYPE
			SYNTAX	INTEGER
			MAX-ACCESS	read-only
			STATUS	current
			::= { hmWanMbus03 34 }

hmWanMbus03Value0E		OBJECT-TYPE
			SYNTAX	INTEGER
			MAX-ACCESS	read-only
			STATUS	current
			::= { hmWanMbus03 35 }

hmWanMbus03VIF0F		OBJECT-TYPE
			SYNTAX	INTEGER
			MAX-ACCESS	read-only
			STATUS	current
			::= { hmWanMbus03 36 }

hmWanMbus03Value0F		OBJECT-TYPE
			SYNTAX	INTEGER
			MAX-ACCESS	read-only
			STATUS	current
			::= { hmWanMbus03 37 }

hmWanMbus03VIF10		OBJECT-TYPE
			SYNTAX	INTEGER
			MAX-ACCESS	read-only
			STATUS	current
			::= { hmWanMbus03 38 }

hmWanMbus03Value10		OBJECT-TYPE
			SYNTAX	INTEGER
			MAX-ACCESS	read-only
			STATUS	current
			::= { hmWanMbus03 39 }

hmWanMbus03VIF11		OBJECT-TYPE
			SYNTAX	INTEGER
			MAX-ACCESS	read-only
			STATUS	current
			::= { hmWanMbus03 40 }

hmWanMbus03Value11		OBJECT-TYPE
			SYNTAX	INTEGER
			MAX-ACCESS	read-only
			STATUS	current
			::= { hmWanMbus03 41 }

hmWanMbus03VIF12		OBJECT-TYPE
			SYNTAX	INTEGER
			MAX-ACCESS	read-only
			STATUS	current
			::= { hmWanMbus03 42 }

hmWanMbus03Value12		OBJECT-TYPE
			SYNTAX	INTEGER
			MAX-ACCESS	read-only
			STATUS	current
			::= { hmWanMbus03 43 }

hmWanMbus03VIF13		OBJECT-TYPE
			SYNTAX	INTEGER
			MAX-ACCESS	read-only
			STATUS	current
			::= { hmWanMbus03 44 }

hmWanMbus03Value13		OBJECT-TYPE
			SYNTAX	INTEGER
			MAX-ACCESS	read-only
			STATUS	current
			::= { hmWanMbus03 45 }

hmWanMbus03VIF14		OBJECT-TYPE
			SYNTAX	INTEGER
			MAX-ACCESS	read-only
			STATUS	current
			::= { hmWanMbus03 46 }

hmWanMbus03Value14		OBJECT-TYPE
			SYNTAX	INTEGER
			MAX-ACCESS	read-only
			STATUS	current
			::= { hmWanMbus03 47 }

hmWanMbus03VIF15		OBJECT-TYPE
			SYNTAX	INTEGER
			MAX-ACCESS	read-only
			STATUS	current
			::= { hmWanMbus03 48 }

hmWanMbus03Value15		OBJECT-TYPE
			SYNTAX	INTEGER
			MAX-ACCESS	read-only
			STATUS	current
			::= { hmWanMbus03 49 }

hmWanMbus03VIF16		OBJECT-TYPE
			SYNTAX	INTEGER
			MAX-ACCESS	read-only
			STATUS	current
			::= { hmWanMbus03 50 }

hmWanMbus03Value16		OBJECT-TYPE
			SYNTAX	INTEGER
			MAX-ACCESS	read-only
			STATUS	current
			::= { hmWanMbus03 51 }

hmWanMbus03VIF17		OBJECT-TYPE
			SYNTAX	INTEGER
			MAX-ACCESS	read-only
			STATUS	current
			::= { hmWanMbus03 52 }

hmWanMbus03Value17		OBJECT-TYPE
			SYNTAX	INTEGER
			MAX-ACCESS	read-only
			STATUS	current
			::= { hmWanMbus03 53 }

hmWanMbus03VIF18		OBJECT-TYPE
			SYNTAX	INTEGER
			MAX-ACCESS	read-only
			STATUS	current
			::= { hmWanMbus03 54 }

hmWanMbus03Value18		OBJECT-TYPE
			SYNTAX	INTEGER
			MAX-ACCESS	read-only
			STATUS	current
			::= { hmWanMbus03 55 }

hmWanMbus03VIF19		OBJECT-TYPE
			SYNTAX	INTEGER
			MAX-ACCESS	read-only
			STATUS	current
			::= { hmWanMbus03 56 }

hmWanMbus03Value19		OBJECT-TYPE
			SYNTAX	INTEGER
			MAX-ACCESS	read-only
			STATUS	current
			::= { hmWanMbus03 57 }

hmWanMbus03VIF1A		OBJECT-TYPE
			SYNTAX	INTEGER
			MAX-ACCESS	read-only
			STATUS	current
			::= { hmWanMbus03 58 }

hmWanMbus03Value1A		OBJECT-TYPE
			SYNTAX	INTEGER
			MAX-ACCESS	read-only
			STATUS	current
			::= { hmWanMbus03 59 }

hmWanMbus03VIF1B		OBJECT-TYPE
			SYNTAX	INTEGER
			MAX-ACCESS	read-only
			STATUS	current
			::= { hmWanMbus03 60 }

hmWanMbus03Value1B		OBJECT-TYPE
			SYNTAX	INTEGER
			MAX-ACCESS	read-only
			STATUS	current
			::= { hmWanMbus03 61 }

hmWanMbus03VIF1C		OBJECT-TYPE
			SYNTAX	INTEGER
			MAX-ACCESS	read-only
			STATUS	current
			::= { hmWanMbus03 62 }

hmWanMbus03Value1C		OBJECT-TYPE
			SYNTAX	INTEGER
			MAX-ACCESS	read-only
			STATUS	current
			::= { hmWanMbus03 63 }

hmWanMbus03VIF1D		OBJECT-TYPE
			SYNTAX	INTEGER
			MAX-ACCESS	read-only
			STATUS	current
			::= { hmWanMbus03 64 }

hmWanMbus03Value1D		OBJECT-TYPE
			SYNTAX	INTEGER
			MAX-ACCESS	read-only
			STATUS	current
			::= { hmWanMbus03 65 }

hmWanMbus03VIF1E		OBJECT-TYPE
			SYNTAX	INTEGER
			MAX-ACCESS	read-only
			STATUS	current
			::= { hmWanMbus03 66 }

hmWanMbus03Value1E		OBJECT-TYPE
			SYNTAX	INTEGER
			MAX-ACCESS	read-only
			STATUS	current
			::= { hmWanMbus03 67 }

hmWanMbus03VIF1F		OBJECT-TYPE
			SYNTAX	INTEGER
			MAX-ACCESS	read-only
			STATUS	current
			::= { hmWanMbus03 68 }

hmWanMbus03Value1F		OBJECT-TYPE
			SYNTAX	INTEGER
			MAX-ACCESS	read-only
			STATUS	current
			::= { hmWanMbus03 69 }

hmWanMbus03VIF20		OBJECT-TYPE
			SYNTAX	INTEGER
			MAX-ACCESS	read-only
			STATUS	current
			::= { hmWanMbus03 70 }

hmWanMbus03Value20		OBJECT-TYPE
			SYNTAX	INTEGER
			MAX-ACCESS	read-only
			STATUS	current
			::= { hmWanMbus03 71 }

hmWanMbus03VIF21		OBJECT-TYPE
			SYNTAX	INTEGER
			MAX-ACCESS	read-only
			STATUS	current
			::= { hmWanMbus03 72 }

hmWanMbus03Value21		OBJECT-TYPE
			SYNTAX	INTEGER
			MAX-ACCESS	read-only
			STATUS	current
			::= { hmWanMbus03 73 }

hmWanMbus03VIF22		OBJECT-TYPE
			SYNTAX	INTEGER
			MAX-ACCESS	read-only
			STATUS	current
			::= { hmWanMbus03 74 }

hmWanMbus03Value22		OBJECT-TYPE
			SYNTAX	INTEGER
			MAX-ACCESS	read-only
			STATUS	current
			::= { hmWanMbus03 75 }

hmWanMbus03VIF23		OBJECT-TYPE
			SYNTAX	INTEGER
			MAX-ACCESS	read-only
			STATUS	current
			::= { hmWanMbus03 76 }

hmWanMbus03Value23		OBJECT-TYPE
			SYNTAX	INTEGER
			MAX-ACCESS	read-only
			STATUS	current
			::= { hmWanMbus03 77 }

hmWanMbus03VIF24		OBJECT-TYPE
			SYNTAX	INTEGER
			MAX-ACCESS	read-only
			STATUS	current
			::= { hmWanMbus03 78 }

hmWanMbus03Value24		OBJECT-TYPE
			SYNTAX	INTEGER
			MAX-ACCESS	read-only
			STATUS	current
			::= { hmWanMbus03 79 }

hmWanMbus03VIF25		OBJECT-TYPE
			SYNTAX	INTEGER
			MAX-ACCESS	read-only
			STATUS	current
			::= { hmWanMbus03 80 }

hmWanMbus03Value25		OBJECT-TYPE
			SYNTAX	INTEGER
			MAX-ACCESS	read-only
			STATUS	current
			::= { hmWanMbus03 81 }

hmWanMbus03VIF26		OBJECT-TYPE
			SYNTAX	INTEGER
			MAX-ACCESS	read-only
			STATUS	current
			::= { hmWanMbus03 82 }

hmWanMbus03Value26		OBJECT-TYPE
			SYNTAX	INTEGER
			MAX-ACCESS	read-only
			STATUS	current
			::= { hmWanMbus03 83 }

hmWanMbus03VIF27		OBJECT-TYPE
			SYNTAX	INTEGER
			MAX-ACCESS	read-only
			STATUS	current
			::= { hmWanMbus03 84 }

hmWanMbus03Value27		OBJECT-TYPE
			SYNTAX	INTEGER
			MAX-ACCESS	read-only
			STATUS	current
			::= { hmWanMbus03 85 }

hmWanMbus03VIF28		OBJECT-TYPE
			SYNTAX	INTEGER
			MAX-ACCESS	read-only
			STATUS	current
			::= { hmWanMbus03 86 }

hmWanMbus03Value28		OBJECT-TYPE
			SYNTAX	INTEGER
			MAX-ACCESS	read-only
			STATUS	current
			::= { hmWanMbus03 87 }

hmWanMbus03VIF29		OBJECT-TYPE
			SYNTAX	INTEGER
			MAX-ACCESS	read-only
			STATUS	current
			::= { hmWanMbus03 88 }

hmWanMbus03Value29		OBJECT-TYPE
			SYNTAX	INTEGER
			MAX-ACCESS	read-only
			STATUS	current
			::= { hmWanMbus03 89 }

hmWanMbus03VIF2A		OBJECT-TYPE
			SYNTAX	INTEGER
			MAX-ACCESS	read-only
			STATUS	current
			::= { hmWanMbus03 90 }

hmWanMbus03Value2A		OBJECT-TYPE
			SYNTAX	INTEGER
			MAX-ACCESS	read-only
			STATUS	current
			::= { hmWanMbus03 91 }

hmWanMbus03VIF2B		OBJECT-TYPE
			SYNTAX	INTEGER
			MAX-ACCESS	read-only
			STATUS	current
			::= { hmWanMbus03 92 }

hmWanMbus03Value2B		OBJECT-TYPE
			SYNTAX	INTEGER
			MAX-ACCESS	read-only
			STATUS	current
			::= { hmWanMbus03 93 }

hmWanMbus03VIF2C		OBJECT-TYPE
			SYNTAX	INTEGER
			MAX-ACCESS	read-only
			STATUS	current
			::= { hmWanMbus03 94 }

hmWanMbus03Value2C		OBJECT-TYPE
			SYNTAX	INTEGER
			MAX-ACCESS	read-only
			STATUS	current
			::= { hmWanMbus03 95 }

hmWanMbus03VIF2D		OBJECT-TYPE
			SYNTAX	INTEGER
			MAX-ACCESS	read-only
			STATUS	current
			::= { hmWanMbus03 96 }

hmWanMbus03Value2D		OBJECT-TYPE
			SYNTAX	INTEGER
			MAX-ACCESS	read-only
			STATUS	current
			::= { hmWanMbus03 97 }

hmWanMbus03VIF2E		OBJECT-TYPE
			SYNTAX	INTEGER
			MAX-ACCESS	read-only
			STATUS	current
			::= { hmWanMbus03 98 }

hmWanMbus03Value2E		OBJECT-TYPE
			SYNTAX	INTEGER
			MAX-ACCESS	read-only
			STATUS	current
			::= { hmWanMbus03 99 }

hmWanMbus03VIF2F		OBJECT-TYPE
			SYNTAX	INTEGER
			MAX-ACCESS	read-only
			STATUS	current
			::= { hmWanMbus03 100 }

hmWanMbus03Value2F		OBJECT-TYPE
			SYNTAX	INTEGER
			MAX-ACCESS	read-only
			STATUS	current
			::= { hmWanMbus03 101 }

hmWanMbus04			OBJECT IDENTIFIER ::= { hmWanMbus 4 }

hmWanMbus04IdNumber		OBJECT-TYPE
			SYNTAX	Gauge32
			MAX-ACCESS	read-only
			STATUS	current
			::= { hmWanMbus04 1 }

hmWanMbus04Manufacturer	OBJECT-TYPE
			SYNTAX	Gauge32
			MAX-ACCESS	read-only
			STATUS	current
			::= { hmWanMbus04 2 }

hmWanMbus04Version		OBJECT-TYPE
			SYNTAX	Gauge32
			MAX-ACCESS	read-only
			STATUS	current
			::= { hmWanMbus04 3 }

hmWanMbus04Medium		OBJECT-TYPE
			SYNTAX	Gauge32
			MAX-ACCESS	read-only
			STATUS	current
			::= { hmWanMbus04 4 }

hmWanMbus04Status		OBJECT-TYPE
			SYNTAX	Gauge32
			MAX-ACCESS	read-only
			STATUS	current
			::= { hmWanMbus04 5 }

hmWanMbus04VIF00		OBJECT-TYPE
			SYNTAX	INTEGER
			MAX-ACCESS	read-only
			STATUS	current
			::= { hmWanMbus04 6 }

hmWanMbus04Value00		OBJECT-TYPE
			SYNTAX	INTEGER
			MAX-ACCESS	read-only
			STATUS	current
			::= { hmWanMbus04 7 }

hmWanMbus04VIF01		OBJECT-TYPE
			SYNTAX	INTEGER
			MAX-ACCESS	read-only
			STATUS	current
			::= { hmWanMbus04 8 }

hmWanMbus04Value01		OBJECT-TYPE
			SYNTAX	INTEGER
			MAX-ACCESS	read-only
			STATUS	current
			::= { hmWanMbus04 9 }

hmWanMbus04VIF02		OBJECT-TYPE
			SYNTAX	INTEGER
			MAX-ACCESS	read-only
			STATUS	current
			::= { hmWanMbus04 10 }

hmWanMbus04Value02		OBJECT-TYPE
			SYNTAX	INTEGER
			MAX-ACCESS	read-only
			STATUS	current
			::= { hmWanMbus04 11 }

hmWanMbus04VIF03		OBJECT-TYPE
			SYNTAX	INTEGER
			MAX-ACCESS	read-only
			STATUS	current
			::= { hmWanMbus04 12 }

hmWanMbus04Value03		OBJECT-TYPE
			SYNTAX	INTEGER
			MAX-ACCESS	read-only
			STATUS	current
			::= { hmWanMbus04 13 }

hmWanMbus04VIF04		OBJECT-TYPE
			SYNTAX	INTEGER
			MAX-ACCESS	read-only
			STATUS	current
			::= { hmWanMbus04 14 }

hmWanMbus04Value04		OBJECT-TYPE
			SYNTAX	INTEGER
			MAX-ACCESS	read-only
			STATUS	current
			::= { hmWanMbus04 15 }

hmWanMbus04VIF05		OBJECT-TYPE
			SYNTAX	INTEGER
			MAX-ACCESS	read-only
			STATUS	current
			::= { hmWanMbus04 16 }

hmWanMbus04Value05		OBJECT-TYPE
			SYNTAX	INTEGER
			MAX-ACCESS	read-only
			STATUS	current
			::= { hmWanMbus04 17 }

hmWanMbus04VIF06		OBJECT-TYPE
			SYNTAX	INTEGER
			MAX-ACCESS	read-only
			STATUS	current
			::= { hmWanMbus04 18 }

hmWanMbus04Value06		OBJECT-TYPE
			SYNTAX	INTEGER
			MAX-ACCESS	read-only
			STATUS	current
			::= { hmWanMbus04 19 }

hmWanMbus04VIF07		OBJECT-TYPE
			SYNTAX	INTEGER
			MAX-ACCESS	read-only
			STATUS	current
			::= { hmWanMbus04 20 }

hmWanMbus04Value07		OBJECT-TYPE
			SYNTAX	INTEGER
			MAX-ACCESS	read-only
			STATUS	current
			::= { hmWanMbus04 21 }

hmWanMbus04VIF08		OBJECT-TYPE
			SYNTAX	INTEGER
			MAX-ACCESS	read-only
			STATUS	current
			::= { hmWanMbus04 22 }

hmWanMbus04Value08		OBJECT-TYPE
			SYNTAX	INTEGER
			MAX-ACCESS	read-only
			STATUS	current
			::= { hmWanMbus04 23 }

hmWanMbus04VIF09		OBJECT-TYPE
			SYNTAX	INTEGER
			MAX-ACCESS	read-only
			STATUS	current
			::= { hmWanMbus04 24 }

hmWanMbus04Value09		OBJECT-TYPE
			SYNTAX	INTEGER
			MAX-ACCESS	read-only
			STATUS	current
			::= { hmWanMbus04 25 }

hmWanMbus04VIF0A		OBJECT-TYPE
			SYNTAX	INTEGER
			MAX-ACCESS	read-only
			STATUS	current
			::= { hmWanMbus04 26 }

hmWanMbus04Value0A		OBJECT-TYPE
			SYNTAX	INTEGER
			MAX-ACCESS	read-only
			STATUS	current
			::= { hmWanMbus04 27 }

hmWanMbus04VIF0B		OBJECT-TYPE
			SYNTAX	INTEGER
			MAX-ACCESS	read-only
			STATUS	current
			::= { hmWanMbus04 28 }

hmWanMbus04Value0B		OBJECT-TYPE
			SYNTAX	INTEGER
			MAX-ACCESS	read-only
			STATUS	current
			::= { hmWanMbus04 29 }

hmWanMbus04VIF0C		OBJECT-TYPE
			SYNTAX	INTEGER
			MAX-ACCESS	read-only
			STATUS	current
			::= { hmWanMbus04 30 }

hmWanMbus04Value0C		OBJECT-TYPE
			SYNTAX	INTEGER
			MAX-ACCESS	read-only
			STATUS	current
			::= { hmWanMbus04 31 }

hmWanMbus04VIF0D		OBJECT-TYPE
			SYNTAX	INTEGER
			MAX-ACCESS	read-only
			STATUS	current
			::= { hmWanMbus04 32 }

hmWanMbus04Value0D		OBJECT-TYPE
			SYNTAX	INTEGER
			MAX-ACCESS	read-only
			STATUS	current
			::= { hmWanMbus04 33 }

hmWanMbus04VIF0E		OBJECT-TYPE
			SYNTAX	INTEGER
			MAX-ACCESS	read-only
			STATUS	current
			::= { hmWanMbus04 34 }

hmWanMbus04Value0E		OBJECT-TYPE
			SYNTAX	INTEGER
			MAX-ACCESS	read-only
			STATUS	current
			::= { hmWanMbus04 35 }

hmWanMbus04VIF0F		OBJECT-TYPE
			SYNTAX	INTEGER
			MAX-ACCESS	read-only
			STATUS	current
			::= { hmWanMbus04 36 }

hmWanMbus04Value0F		OBJECT-TYPE
			SYNTAX	INTEGER
			MAX-ACCESS	read-only
			STATUS	current
			::= { hmWanMbus04 37 }

hmWanMbus04VIF10		OBJECT-TYPE
			SYNTAX	INTEGER
			MAX-ACCESS	read-only
			STATUS	current
			::= { hmWanMbus04 38 }

hmWanMbus04Value10		OBJECT-TYPE
			SYNTAX	INTEGER
			MAX-ACCESS	read-only
			STATUS	current
			::= { hmWanMbus04 39 }

hmWanMbus04VIF11		OBJECT-TYPE
			SYNTAX	INTEGER
			MAX-ACCESS	read-only
			STATUS	current
			::= { hmWanMbus04 40 }

hmWanMbus04Value11		OBJECT-TYPE
			SYNTAX	INTEGER
			MAX-ACCESS	read-only
			STATUS	current
			::= { hmWanMbus04 41 }

hmWanMbus04VIF12		OBJECT-TYPE
			SYNTAX	INTEGER
			MAX-ACCESS	read-only
			STATUS	current
			::= { hmWanMbus04 42 }

hmWanMbus04Value12		OBJECT-TYPE
			SYNTAX	INTEGER
			MAX-ACCESS	read-only
			STATUS	current
			::= { hmWanMbus04 43 }

hmWanMbus04VIF13		OBJECT-TYPE
			SYNTAX	INTEGER
			MAX-ACCESS	read-only
			STATUS	current
			::= { hmWanMbus04 44 }

hmWanMbus04Value13		OBJECT-TYPE
			SYNTAX	INTEGER
			MAX-ACCESS	read-only
			STATUS	current
			::= { hmWanMbus04 45 }

hmWanMbus04VIF14		OBJECT-TYPE
			SYNTAX	INTEGER
			MAX-ACCESS	read-only
			STATUS	current
			::= { hmWanMbus04 46 }

hmWanMbus04Value14		OBJECT-TYPE
			SYNTAX	INTEGER
			MAX-ACCESS	read-only
			STATUS	current
			::= { hmWanMbus04 47 }

hmWanMbus04VIF15		OBJECT-TYPE
			SYNTAX	INTEGER
			MAX-ACCESS	read-only
			STATUS	current
			::= { hmWanMbus04 48 }

hmWanMbus04Value15		OBJECT-TYPE
			SYNTAX	INTEGER
			MAX-ACCESS	read-only
			STATUS	current
			::= { hmWanMbus04 49 }

hmWanMbus04VIF16		OBJECT-TYPE
			SYNTAX	INTEGER
			MAX-ACCESS	read-only
			STATUS	current
			::= { hmWanMbus04 50 }

hmWanMbus04Value16		OBJECT-TYPE
			SYNTAX	INTEGER
			MAX-ACCESS	read-only
			STATUS	current
			::= { hmWanMbus04 51 }

hmWanMbus04VIF17		OBJECT-TYPE
			SYNTAX	INTEGER
			MAX-ACCESS	read-only
			STATUS	current
			::= { hmWanMbus04 52 }

hmWanMbus04Value17		OBJECT-TYPE
			SYNTAX	INTEGER
			MAX-ACCESS	read-only
			STATUS	current
			::= { hmWanMbus04 53 }

hmWanMbus04VIF18		OBJECT-TYPE
			SYNTAX	INTEGER
			MAX-ACCESS	read-only
			STATUS	current
			::= { hmWanMbus04 54 }

hmWanMbus04Value18		OBJECT-TYPE
			SYNTAX	INTEGER
			MAX-ACCESS	read-only
			STATUS	current
			::= { hmWanMbus04 55 }

hmWanMbus04VIF19		OBJECT-TYPE
			SYNTAX	INTEGER
			MAX-ACCESS	read-only
			STATUS	current
			::= { hmWanMbus04 56 }

hmWanMbus04Value19		OBJECT-TYPE
			SYNTAX	INTEGER
			MAX-ACCESS	read-only
			STATUS	current
			::= { hmWanMbus04 57 }

hmWanMbus04VIF1A		OBJECT-TYPE
			SYNTAX	INTEGER
			MAX-ACCESS	read-only
			STATUS	current
			::= { hmWanMbus04 58 }

hmWanMbus04Value1A		OBJECT-TYPE
			SYNTAX	INTEGER
			MAX-ACCESS	read-only
			STATUS	current
			::= { hmWanMbus04 59 }

hmWanMbus04VIF1B		OBJECT-TYPE
			SYNTAX	INTEGER
			MAX-ACCESS	read-only
			STATUS	current
			::= { hmWanMbus04 60 }

hmWanMbus04Value1B		OBJECT-TYPE
			SYNTAX	INTEGER
			MAX-ACCESS	read-only
			STATUS	current
			::= { hmWanMbus04 61 }

hmWanMbus04VIF1C		OBJECT-TYPE
			SYNTAX	INTEGER
			MAX-ACCESS	read-only
			STATUS	current
			::= { hmWanMbus04 62 }

hmWanMbus04Value1C		OBJECT-TYPE
			SYNTAX	INTEGER
			MAX-ACCESS	read-only
			STATUS	current
			::= { hmWanMbus04 63 }

hmWanMbus04VIF1D		OBJECT-TYPE
			SYNTAX	INTEGER
			MAX-ACCESS	read-only
			STATUS	current
			::= { hmWanMbus04 64 }

hmWanMbus04Value1D		OBJECT-TYPE
			SYNTAX	INTEGER
			MAX-ACCESS	read-only
			STATUS	current
			::= { hmWanMbus04 65 }

hmWanMbus04VIF1E		OBJECT-TYPE
			SYNTAX	INTEGER
			MAX-ACCESS	read-only
			STATUS	current
			::= { hmWanMbus04 66 }

hmWanMbus04Value1E		OBJECT-TYPE
			SYNTAX	INTEGER
			MAX-ACCESS	read-only
			STATUS	current
			::= { hmWanMbus04 67 }

hmWanMbus04VIF1F		OBJECT-TYPE
			SYNTAX	INTEGER
			MAX-ACCESS	read-only
			STATUS	current
			::= { hmWanMbus04 68 }

hmWanMbus04Value1F		OBJECT-TYPE
			SYNTAX	INTEGER
			MAX-ACCESS	read-only
			STATUS	current
			::= { hmWanMbus04 69 }

hmWanMbus04VIF20		OBJECT-TYPE
			SYNTAX	INTEGER
			MAX-ACCESS	read-only
			STATUS	current
			::= { hmWanMbus04 70 }

hmWanMbus04Value20		OBJECT-TYPE
			SYNTAX	INTEGER
			MAX-ACCESS	read-only
			STATUS	current
			::= { hmWanMbus04 71 }

hmWanMbus04VIF21		OBJECT-TYPE
			SYNTAX	INTEGER
			MAX-ACCESS	read-only
			STATUS	current
			::= { hmWanMbus04 72 }

hmWanMbus04Value21		OBJECT-TYPE
			SYNTAX	INTEGER
			MAX-ACCESS	read-only
			STATUS	current
			::= { hmWanMbus04 73 }

hmWanMbus04VIF22		OBJECT-TYPE
			SYNTAX	INTEGER
			MAX-ACCESS	read-only
			STATUS	current
			::= { hmWanMbus04 74 }

hmWanMbus04Value22		OBJECT-TYPE
			SYNTAX	INTEGER
			MAX-ACCESS	read-only
			STATUS	current
			::= { hmWanMbus04 75 }

hmWanMbus04VIF23		OBJECT-TYPE
			SYNTAX	INTEGER
			MAX-ACCESS	read-only
			STATUS	current
			::= { hmWanMbus04 76 }

hmWanMbus04Value23		OBJECT-TYPE
			SYNTAX	INTEGER
			MAX-ACCESS	read-only
			STATUS	current
			::= { hmWanMbus04 77 }

hmWanMbus04VIF24		OBJECT-TYPE
			SYNTAX	INTEGER
			MAX-ACCESS	read-only
			STATUS	current
			::= { hmWanMbus04 78 }

hmWanMbus04Value24		OBJECT-TYPE
			SYNTAX	INTEGER
			MAX-ACCESS	read-only
			STATUS	current
			::= { hmWanMbus04 79 }

hmWanMbus04VIF25		OBJECT-TYPE
			SYNTAX	INTEGER
			MAX-ACCESS	read-only
			STATUS	current
			::= { hmWanMbus04 80 }

hmWanMbus04Value25		OBJECT-TYPE
			SYNTAX	INTEGER
			MAX-ACCESS	read-only
			STATUS	current
			::= { hmWanMbus04 81 }

hmWanMbus04VIF26		OBJECT-TYPE
			SYNTAX	INTEGER
			MAX-ACCESS	read-only
			STATUS	current
			::= { hmWanMbus04 82 }

hmWanMbus04Value26		OBJECT-TYPE
			SYNTAX	INTEGER
			MAX-ACCESS	read-only
			STATUS	current
			::= { hmWanMbus04 83 }

hmWanMbus04VIF27		OBJECT-TYPE
			SYNTAX	INTEGER
			MAX-ACCESS	read-only
			STATUS	current
			::= { hmWanMbus04 84 }

hmWanMbus04Value27		OBJECT-TYPE
			SYNTAX	INTEGER
			MAX-ACCESS	read-only
			STATUS	current
			::= { hmWanMbus04 85 }

hmWanMbus04VIF28		OBJECT-TYPE
			SYNTAX	INTEGER
			MAX-ACCESS	read-only
			STATUS	current
			::= { hmWanMbus04 86 }

hmWanMbus04Value28		OBJECT-TYPE
			SYNTAX	INTEGER
			MAX-ACCESS	read-only
			STATUS	current
			::= { hmWanMbus04 87 }

hmWanMbus04VIF29		OBJECT-TYPE
			SYNTAX	INTEGER
			MAX-ACCESS	read-only
			STATUS	current
			::= { hmWanMbus04 88 }

hmWanMbus04Value29		OBJECT-TYPE
			SYNTAX	INTEGER
			MAX-ACCESS	read-only
			STATUS	current
			::= { hmWanMbus04 89 }

hmWanMbus04VIF2A		OBJECT-TYPE
			SYNTAX	INTEGER
			MAX-ACCESS	read-only
			STATUS	current
			::= { hmWanMbus04 90 }

hmWanMbus04Value2A		OBJECT-TYPE
			SYNTAX	INTEGER
			MAX-ACCESS	read-only
			STATUS	current
			::= { hmWanMbus04 91 }

hmWanMbus04VIF2B		OBJECT-TYPE
			SYNTAX	INTEGER
			MAX-ACCESS	read-only
			STATUS	current
			::= { hmWanMbus04 92 }

hmWanMbus04Value2B		OBJECT-TYPE
			SYNTAX	INTEGER
			MAX-ACCESS	read-only
			STATUS	current
			::= { hmWanMbus04 93 }

hmWanMbus04VIF2C		OBJECT-TYPE
			SYNTAX	INTEGER
			MAX-ACCESS	read-only
			STATUS	current
			::= { hmWanMbus04 94 }

hmWanMbus04Value2C		OBJECT-TYPE
			SYNTAX	INTEGER
			MAX-ACCESS	read-only
			STATUS	current
			::= { hmWanMbus04 95 }

hmWanMbus04VIF2D		OBJECT-TYPE
			SYNTAX	INTEGER
			MAX-ACCESS	read-only
			STATUS	current
			::= { hmWanMbus04 96 }

hmWanMbus04Value2D		OBJECT-TYPE
			SYNTAX	INTEGER
			MAX-ACCESS	read-only
			STATUS	current
			::= { hmWanMbus04 97 }

hmWanMbus04VIF2E		OBJECT-TYPE
			SYNTAX	INTEGER
			MAX-ACCESS	read-only
			STATUS	current
			::= { hmWanMbus04 98 }

hmWanMbus04Value2E		OBJECT-TYPE
			SYNTAX	INTEGER
			MAX-ACCESS	read-only
			STATUS	current
			::= { hmWanMbus04 99 }

hmWanMbus04VIF2F		OBJECT-TYPE
			SYNTAX	INTEGER
			MAX-ACCESS	read-only
			STATUS	current
			::= { hmWanMbus04 100 }

hmWanMbus04Value2F		OBJECT-TYPE
			SYNTAX	INTEGER
			MAX-ACCESS	read-only
			STATUS	current
			::= { hmWanMbus04 101 }

hmWanMbus05			OBJECT IDENTIFIER ::= { hmWanMbus 5 }

hmWanMbus05IdNumber		OBJECT-TYPE
			SYNTAX	Gauge32
			MAX-ACCESS	read-only
			STATUS	current
			::= { hmWanMbus05 1 }

hmWanMbus05Manufacturer	OBJECT-TYPE
			SYNTAX	Gauge32
			MAX-ACCESS	read-only
			STATUS	current
			::= { hmWanMbus05 2 }

hmWanMbus05Version		OBJECT-TYPE
			SYNTAX	Gauge32
			MAX-ACCESS	read-only
			STATUS	current
			::= { hmWanMbus05 3 }

hmWanMbus05Medium		OBJECT-TYPE
			SYNTAX	Gauge32
			MAX-ACCESS	read-only
			STATUS	current
			::= { hmWanMbus05 4 }

hmWanMbus05Status		OBJECT-TYPE
			SYNTAX	Gauge32
			MAX-ACCESS	read-only
			STATUS	current
			::= { hmWanMbus05 5 }

hmWanMbus05VIF00		OBJECT-TYPE
			SYNTAX	INTEGER
			MAX-ACCESS	read-only
			STATUS	current
			::= { hmWanMbus05 6 }

hmWanMbus05Value00		OBJECT-TYPE
			SYNTAX	INTEGER
			MAX-ACCESS	read-only
			STATUS	current
			::= { hmWanMbus05 7 }

hmWanMbus05VIF01		OBJECT-TYPE
			SYNTAX	INTEGER
			MAX-ACCESS	read-only
			STATUS	current
			::= { hmWanMbus05 8 }

hmWanMbus05Value01		OBJECT-TYPE
			SYNTAX	INTEGER
			MAX-ACCESS	read-only
			STATUS	current
			::= { hmWanMbus05 9 }

hmWanMbus05VIF02		OBJECT-TYPE
			SYNTAX	INTEGER
			MAX-ACCESS	read-only
			STATUS	current
			::= { hmWanMbus05 10 }

hmWanMbus05Value02		OBJECT-TYPE
			SYNTAX	INTEGER
			MAX-ACCESS	read-only
			STATUS	current
			::= { hmWanMbus05 11 }

hmWanMbus05VIF03		OBJECT-TYPE
			SYNTAX	INTEGER
			MAX-ACCESS	read-only
			STATUS	current
			::= { hmWanMbus05 12 }

hmWanMbus05Value03		OBJECT-TYPE
			SYNTAX	INTEGER
			MAX-ACCESS	read-only
			STATUS	current
			::= { hmWanMbus05 13 }

hmWanMbus05VIF04		OBJECT-TYPE
			SYNTAX	INTEGER
			MAX-ACCESS	read-only
			STATUS	current
			::= { hmWanMbus05 14 }

hmWanMbus05Value04		OBJECT-TYPE
			SYNTAX	INTEGER
			MAX-ACCESS	read-only
			STATUS	current
			::= { hmWanMbus05 15 }

hmWanMbus05VIF05		OBJECT-TYPE
			SYNTAX	INTEGER
			MAX-ACCESS	read-only
			STATUS	current
			::= { hmWanMbus05 16 }

hmWanMbus05Value05		OBJECT-TYPE
			SYNTAX	INTEGER
			MAX-ACCESS	read-only
			STATUS	current
			::= { hmWanMbus05 17 }

hmWanMbus05VIF06		OBJECT-TYPE
			SYNTAX	INTEGER
			MAX-ACCESS	read-only
			STATUS	current
			::= { hmWanMbus05 18 }

hmWanMbus05Value06		OBJECT-TYPE
			SYNTAX	INTEGER
			MAX-ACCESS	read-only
			STATUS	current
			::= { hmWanMbus05 19 }

hmWanMbus05VIF07		OBJECT-TYPE
			SYNTAX	INTEGER
			MAX-ACCESS	read-only
			STATUS	current
			::= { hmWanMbus05 20 }

hmWanMbus05Value07		OBJECT-TYPE
			SYNTAX	INTEGER
			MAX-ACCESS	read-only
			STATUS	current
			::= { hmWanMbus05 21 }

hmWanMbus05VIF08		OBJECT-TYPE
			SYNTAX	INTEGER
			MAX-ACCESS	read-only
			STATUS	current
			::= { hmWanMbus05 22 }

hmWanMbus05Value08		OBJECT-TYPE
			SYNTAX	INTEGER
			MAX-ACCESS	read-only
			STATUS	current
			::= { hmWanMbus05 23 }

hmWanMbus05VIF09		OBJECT-TYPE
			SYNTAX	INTEGER
			MAX-ACCESS	read-only
			STATUS	current
			::= { hmWanMbus05 24 }

hmWanMbus05Value09		OBJECT-TYPE
			SYNTAX	INTEGER
			MAX-ACCESS	read-only
			STATUS	current
			::= { hmWanMbus05 25 }

hmWanMbus05VIF0A		OBJECT-TYPE
			SYNTAX	INTEGER
			MAX-ACCESS	read-only
			STATUS	current
			::= { hmWanMbus05 26 }

hmWanMbus05Value0A		OBJECT-TYPE
			SYNTAX	INTEGER
			MAX-ACCESS	read-only
			STATUS	current
			::= { hmWanMbus05 27 }

hmWanMbus05VIF0B		OBJECT-TYPE
			SYNTAX	INTEGER
			MAX-ACCESS	read-only
			STATUS	current
			::= { hmWanMbus05 28 }

hmWanMbus05Value0B		OBJECT-TYPE
			SYNTAX	INTEGER
			MAX-ACCESS	read-only
			STATUS	current
			::= { hmWanMbus05 29 }

hmWanMbus05VIF0C		OBJECT-TYPE
			SYNTAX	INTEGER
			MAX-ACCESS	read-only
			STATUS	current
			::= { hmWanMbus05 30 }

hmWanMbus05Value0C		OBJECT-TYPE
			SYNTAX	INTEGER
			MAX-ACCESS	read-only
			STATUS	current
			::= { hmWanMbus05 31 }

hmWanMbus05VIF0D		OBJECT-TYPE
			SYNTAX	INTEGER
			MAX-ACCESS	read-only
			STATUS	current
			::= { hmWanMbus05 32 }

hmWanMbus05Value0D		OBJECT-TYPE
			SYNTAX	INTEGER
			MAX-ACCESS	read-only
			STATUS	current
			::= { hmWanMbus05 33 }

hmWanMbus05VIF0E		OBJECT-TYPE
			SYNTAX	INTEGER
			MAX-ACCESS	read-only
			STATUS	current
			::= { hmWanMbus05 34 }

hmWanMbus05Value0E		OBJECT-TYPE
			SYNTAX	INTEGER
			MAX-ACCESS	read-only
			STATUS	current
			::= { hmWanMbus05 35 }

hmWanMbus05VIF0F		OBJECT-TYPE
			SYNTAX	INTEGER
			MAX-ACCESS	read-only
			STATUS	current
			::= { hmWanMbus05 36 }

hmWanMbus05Value0F		OBJECT-TYPE
			SYNTAX	INTEGER
			MAX-ACCESS	read-only
			STATUS	current
			::= { hmWanMbus05 37 }

hmWanMbus05VIF10		OBJECT-TYPE
			SYNTAX	INTEGER
			MAX-ACCESS	read-only
			STATUS	current
			::= { hmWanMbus05 38 }

hmWanMbus05Value10		OBJECT-TYPE
			SYNTAX	INTEGER
			MAX-ACCESS	read-only
			STATUS	current
			::= { hmWanMbus05 39 }

hmWanMbus05VIF11		OBJECT-TYPE
			SYNTAX	INTEGER
			MAX-ACCESS	read-only
			STATUS	current
			::= { hmWanMbus05 40 }

hmWanMbus05Value11		OBJECT-TYPE
			SYNTAX	INTEGER
			MAX-ACCESS	read-only
			STATUS	current
			::= { hmWanMbus05 41 }

hmWanMbus05VIF12		OBJECT-TYPE
			SYNTAX	INTEGER
			MAX-ACCESS	read-only
			STATUS	current
			::= { hmWanMbus05 42 }

hmWanMbus05Value12		OBJECT-TYPE
			SYNTAX	INTEGER
			MAX-ACCESS	read-only
			STATUS	current
			::= { hmWanMbus05 43 }

hmWanMbus05VIF13		OBJECT-TYPE
			SYNTAX	INTEGER
			MAX-ACCESS	read-only
			STATUS	current
			::= { hmWanMbus05 44 }

hmWanMbus05Value13		OBJECT-TYPE
			SYNTAX	INTEGER
			MAX-ACCESS	read-only
			STATUS	current
			::= { hmWanMbus05 45 }

hmWanMbus05VIF14		OBJECT-TYPE
			SYNTAX	INTEGER
			MAX-ACCESS	read-only
			STATUS	current
			::= { hmWanMbus05 46 }

hmWanMbus05Value14		OBJECT-TYPE
			SYNTAX	INTEGER
			MAX-ACCESS	read-only
			STATUS	current
			::= { hmWanMbus05 47 }

hmWanMbus05VIF15		OBJECT-TYPE
			SYNTAX	INTEGER
			MAX-ACCESS	read-only
			STATUS	current
			::= { hmWanMbus05 48 }

hmWanMbus05Value15		OBJECT-TYPE
			SYNTAX	INTEGER
			MAX-ACCESS	read-only
			STATUS	current
			::= { hmWanMbus05 49 }

hmWanMbus05VIF16		OBJECT-TYPE
			SYNTAX	INTEGER
			MAX-ACCESS	read-only
			STATUS	current
			::= { hmWanMbus05 50 }

hmWanMbus05Value16		OBJECT-TYPE
			SYNTAX	INTEGER
			MAX-ACCESS	read-only
			STATUS	current
			::= { hmWanMbus05 51 }

hmWanMbus05VIF17		OBJECT-TYPE
			SYNTAX	INTEGER
			MAX-ACCESS	read-only
			STATUS	current
			::= { hmWanMbus05 52 }

hmWanMbus05Value17		OBJECT-TYPE
			SYNTAX	INTEGER
			MAX-ACCESS	read-only
			STATUS	current
			::= { hmWanMbus05 53 }

hmWanMbus05VIF18		OBJECT-TYPE
			SYNTAX	INTEGER
			MAX-ACCESS	read-only
			STATUS	current
			::= { hmWanMbus05 54 }

hmWanMbus05Value18		OBJECT-TYPE
			SYNTAX	INTEGER
			MAX-ACCESS	read-only
			STATUS	current
			::= { hmWanMbus05 55 }

hmWanMbus05VIF19		OBJECT-TYPE
			SYNTAX	INTEGER
			MAX-ACCESS	read-only
			STATUS	current
			::= { hmWanMbus05 56 }

hmWanMbus05Value19		OBJECT-TYPE
			SYNTAX	INTEGER
			MAX-ACCESS	read-only
			STATUS	current
			::= { hmWanMbus05 57 }

hmWanMbus05VIF1A		OBJECT-TYPE
			SYNTAX	INTEGER
			MAX-ACCESS	read-only
			STATUS	current
			::= { hmWanMbus05 58 }

hmWanMbus05Value1A		OBJECT-TYPE
			SYNTAX	INTEGER
			MAX-ACCESS	read-only
			STATUS	current
			::= { hmWanMbus05 59 }

hmWanMbus05VIF1B		OBJECT-TYPE
			SYNTAX	INTEGER
			MAX-ACCESS	read-only
			STATUS	current
			::= { hmWanMbus05 60 }

hmWanMbus05Value1B		OBJECT-TYPE
			SYNTAX	INTEGER
			MAX-ACCESS	read-only
			STATUS	current
			::= { hmWanMbus05 61 }

hmWanMbus05VIF1C		OBJECT-TYPE
			SYNTAX	INTEGER
			MAX-ACCESS	read-only
			STATUS	current
			::= { hmWanMbus05 62 }

hmWanMbus05Value1C		OBJECT-TYPE
			SYNTAX	INTEGER
			MAX-ACCESS	read-only
			STATUS	current
			::= { hmWanMbus05 63 }

hmWanMbus05VIF1D		OBJECT-TYPE
			SYNTAX	INTEGER
			MAX-ACCESS	read-only
			STATUS	current
			::= { hmWanMbus05 64 }

hmWanMbus05Value1D		OBJECT-TYPE
			SYNTAX	INTEGER
			MAX-ACCESS	read-only
			STATUS	current
			::= { hmWanMbus05 65 }

hmWanMbus05VIF1E		OBJECT-TYPE
			SYNTAX	INTEGER
			MAX-ACCESS	read-only
			STATUS	current
			::= { hmWanMbus05 66 }

hmWanMbus05Value1E		OBJECT-TYPE
			SYNTAX	INTEGER
			MAX-ACCESS	read-only
			STATUS	current
			::= { hmWanMbus05 67 }

hmWanMbus05VIF1F		OBJECT-TYPE
			SYNTAX	INTEGER
			MAX-ACCESS	read-only
			STATUS	current
			::= { hmWanMbus05 68 }

hmWanMbus05Value1F		OBJECT-TYPE
			SYNTAX	INTEGER
			MAX-ACCESS	read-only
			STATUS	current
			::= { hmWanMbus05 69 }

hmWanMbus05VIF20		OBJECT-TYPE
			SYNTAX	INTEGER
			MAX-ACCESS	read-only
			STATUS	current
			::= { hmWanMbus05 70 }

hmWanMbus05Value20		OBJECT-TYPE
			SYNTAX	INTEGER
			MAX-ACCESS	read-only
			STATUS	current
			::= { hmWanMbus05 71 }

hmWanMbus05VIF21		OBJECT-TYPE
			SYNTAX	INTEGER
			MAX-ACCESS	read-only
			STATUS	current
			::= { hmWanMbus05 72 }

hmWanMbus05Value21		OBJECT-TYPE
			SYNTAX	INTEGER
			MAX-ACCESS	read-only
			STATUS	current
			::= { hmWanMbus05 73 }

hmWanMbus05VIF22		OBJECT-TYPE
			SYNTAX	INTEGER
			MAX-ACCESS	read-only
			STATUS	current
			::= { hmWanMbus05 74 }

hmWanMbus05Value22		OBJECT-TYPE
			SYNTAX	INTEGER
			MAX-ACCESS	read-only
			STATUS	current
			::= { hmWanMbus05 75 }

hmWanMbus05VIF23		OBJECT-TYPE
			SYNTAX	INTEGER
			MAX-ACCESS	read-only
			STATUS	current
			::= { hmWanMbus05 76 }

hmWanMbus05Value23		OBJECT-TYPE
			SYNTAX	INTEGER
			MAX-ACCESS	read-only
			STATUS	current
			::= { hmWanMbus05 77 }

hmWanMbus05VIF24		OBJECT-TYPE
			SYNTAX	INTEGER
			MAX-ACCESS	read-only
			STATUS	current
			::= { hmWanMbus05 78 }

hmWanMbus05Value24		OBJECT-TYPE
			SYNTAX	INTEGER
			MAX-ACCESS	read-only
			STATUS	current
			::= { hmWanMbus05 79 }

hmWanMbus05VIF25		OBJECT-TYPE
			SYNTAX	INTEGER
			MAX-ACCESS	read-only
			STATUS	current
			::= { hmWanMbus05 80 }

hmWanMbus05Value25		OBJECT-TYPE
			SYNTAX	INTEGER
			MAX-ACCESS	read-only
			STATUS	current
			::= { hmWanMbus05 81 }

hmWanMbus05VIF26		OBJECT-TYPE
			SYNTAX	INTEGER
			MAX-ACCESS	read-only
			STATUS	current
			::= { hmWanMbus05 82 }

hmWanMbus05Value26		OBJECT-TYPE
			SYNTAX	INTEGER
			MAX-ACCESS	read-only
			STATUS	current
			::= { hmWanMbus05 83 }

hmWanMbus05VIF27		OBJECT-TYPE
			SYNTAX	INTEGER
			MAX-ACCESS	read-only
			STATUS	current
			::= { hmWanMbus05 84 }

hmWanMbus05Value27		OBJECT-TYPE
			SYNTAX	INTEGER
			MAX-ACCESS	read-only
			STATUS	current
			::= { hmWanMbus05 85 }

hmWanMbus05VIF28		OBJECT-TYPE
			SYNTAX	INTEGER
			MAX-ACCESS	read-only
			STATUS	current
			::= { hmWanMbus05 86 }

hmWanMbus05Value28		OBJECT-TYPE
			SYNTAX	INTEGER
			MAX-ACCESS	read-only
			STATUS	current
			::= { hmWanMbus05 87 }

hmWanMbus05VIF29		OBJECT-TYPE
			SYNTAX	INTEGER
			MAX-ACCESS	read-only
			STATUS	current
			::= { hmWanMbus05 88 }

hmWanMbus05Value29		OBJECT-TYPE
			SYNTAX	INTEGER
			MAX-ACCESS	read-only
			STATUS	current
			::= { hmWanMbus05 89 }

hmWanMbus05VIF2A		OBJECT-TYPE
			SYNTAX	INTEGER
			MAX-ACCESS	read-only
			STATUS	current
			::= { hmWanMbus05 90 }

hmWanMbus05Value2A		OBJECT-TYPE
			SYNTAX	INTEGER
			MAX-ACCESS	read-only
			STATUS	current
			::= { hmWanMbus05 91 }

hmWanMbus05VIF2B		OBJECT-TYPE
			SYNTAX	INTEGER
			MAX-ACCESS	read-only
			STATUS	current
			::= { hmWanMbus05 92 }

hmWanMbus05Value2B		OBJECT-TYPE
			SYNTAX	INTEGER
			MAX-ACCESS	read-only
			STATUS	current
			::= { hmWanMbus05 93 }

hmWanMbus05VIF2C		OBJECT-TYPE
			SYNTAX	INTEGER
			MAX-ACCESS	read-only
			STATUS	current
			::= { hmWanMbus05 94 }

hmWanMbus05Value2C		OBJECT-TYPE
			SYNTAX	INTEGER
			MAX-ACCESS	read-only
			STATUS	current
			::= { hmWanMbus05 95 }

hmWanMbus05VIF2D		OBJECT-TYPE
			SYNTAX	INTEGER
			MAX-ACCESS	read-only
			STATUS	current
			::= { hmWanMbus05 96 }

hmWanMbus05Value2D		OBJECT-TYPE
			SYNTAX	INTEGER
			MAX-ACCESS	read-only
			STATUS	current
			::= { hmWanMbus05 97 }

hmWanMbus05VIF2E		OBJECT-TYPE
			SYNTAX	INTEGER
			MAX-ACCESS	read-only
			STATUS	current
			::= { hmWanMbus05 98 }

hmWanMbus05Value2E		OBJECT-TYPE
			SYNTAX	INTEGER
			MAX-ACCESS	read-only
			STATUS	current
			::= { hmWanMbus05 99 }

hmWanMbus05VIF2F		OBJECT-TYPE
			SYNTAX	INTEGER
			MAX-ACCESS	read-only
			STATUS	current
			::= { hmWanMbus05 100 }

hmWanMbus05Value2F		OBJECT-TYPE
			SYNTAX	INTEGER
			MAX-ACCESS	read-only
			STATUS	current
			::= { hmWanMbus05 101 }

hmWanMbus06			OBJECT IDENTIFIER ::= { hmWanMbus 6 }

hmWanMbus06IdNumber		OBJECT-TYPE
			SYNTAX	Gauge32
			MAX-ACCESS	read-only
			STATUS	current
			::= { hmWanMbus06 1 }

hmWanMbus06Manufacturer	OBJECT-TYPE
			SYNTAX	Gauge32
			MAX-ACCESS	read-only
			STATUS	current
			::= { hmWanMbus06 2 }

hmWanMbus06Version		OBJECT-TYPE
			SYNTAX	Gauge32
			MAX-ACCESS	read-only
			STATUS	current
			::= { hmWanMbus06 3 }

hmWanMbus06Medium		OBJECT-TYPE
			SYNTAX	Gauge32
			MAX-ACCESS	read-only
			STATUS	current
			::= { hmWanMbus06 4 }

hmWanMbus06Status		OBJECT-TYPE
			SYNTAX	Gauge32
			MAX-ACCESS	read-only
			STATUS	current
			::= { hmWanMbus06 5 }

hmWanMbus06VIF00		OBJECT-TYPE
			SYNTAX	INTEGER
			MAX-ACCESS	read-only
			STATUS	current
			::= { hmWanMbus06 6 }

hmWanMbus06Value00		OBJECT-TYPE
			SYNTAX	INTEGER
			MAX-ACCESS	read-only
			STATUS	current
			::= { hmWanMbus06 7 }

hmWanMbus06VIF01		OBJECT-TYPE
			SYNTAX	INTEGER
			MAX-ACCESS	read-only
			STATUS	current
			::= { hmWanMbus06 8 }

hmWanMbus06Value01		OBJECT-TYPE
			SYNTAX	INTEGER
			MAX-ACCESS	read-only
			STATUS	current
			::= { hmWanMbus06 9 }

hmWanMbus06VIF02		OBJECT-TYPE
			SYNTAX	INTEGER
			MAX-ACCESS	read-only
			STATUS	current
			::= { hmWanMbus06 10 }

hmWanMbus06Value02		OBJECT-TYPE
			SYNTAX	INTEGER
			MAX-ACCESS	read-only
			STATUS	current
			::= { hmWanMbus06 11 }

hmWanMbus06VIF03		OBJECT-TYPE
			SYNTAX	INTEGER
			MAX-ACCESS	read-only
			STATUS	current
			::= { hmWanMbus06 12 }

hmWanMbus06Value03		OBJECT-TYPE
			SYNTAX	INTEGER
			MAX-ACCESS	read-only
			STATUS	current
			::= { hmWanMbus06 13 }

hmWanMbus06VIF04		OBJECT-TYPE
			SYNTAX	INTEGER
			MAX-ACCESS	read-only
			STATUS	current
			::= { hmWanMbus06 14 }

hmWanMbus06Value04		OBJECT-TYPE
			SYNTAX	INTEGER
			MAX-ACCESS	read-only
			STATUS	current
			::= { hmWanMbus06 15 }

hmWanMbus06VIF05		OBJECT-TYPE
			SYNTAX	INTEGER
			MAX-ACCESS	read-only
			STATUS	current
			::= { hmWanMbus06 16 }

hmWanMbus06Value05		OBJECT-TYPE
			SYNTAX	INTEGER
			MAX-ACCESS	read-only
			STATUS	current
			::= { hmWanMbus06 17 }

hmWanMbus06VIF06		OBJECT-TYPE
			SYNTAX	INTEGER
			MAX-ACCESS	read-only
			STATUS	current
			::= { hmWanMbus06 18 }

hmWanMbus06Value06		OBJECT-TYPE
			SYNTAX	INTEGER
			MAX-ACCESS	read-only
			STATUS	current
			::= { hmWanMbus06 19 }

hmWanMbus06VIF07		OBJECT-TYPE
			SYNTAX	INTEGER
			MAX-ACCESS	read-only
			STATUS	current
			::= { hmWanMbus06 20 }

hmWanMbus06Value07		OBJECT-TYPE
			SYNTAX	INTEGER
			MAX-ACCESS	read-only
			STATUS	current
			::= { hmWanMbus06 21 }

hmWanMbus06VIF08		OBJECT-TYPE
			SYNTAX	INTEGER
			MAX-ACCESS	read-only
			STATUS	current
			::= { hmWanMbus06 22 }

hmWanMbus06Value08		OBJECT-TYPE
			SYNTAX	INTEGER
			MAX-ACCESS	read-only
			STATUS	current
			::= { hmWanMbus06 23 }

hmWanMbus06VIF09		OBJECT-TYPE
			SYNTAX	INTEGER
			MAX-ACCESS	read-only
			STATUS	current
			::= { hmWanMbus06 24 }

hmWanMbus06Value09		OBJECT-TYPE
			SYNTAX	INTEGER
			MAX-ACCESS	read-only
			STATUS	current
			::= { hmWanMbus06 25 }

hmWanMbus06VIF0A		OBJECT-TYPE
			SYNTAX	INTEGER
			MAX-ACCESS	read-only
			STATUS	current
			::= { hmWanMbus06 26 }

hmWanMbus06Value0A		OBJECT-TYPE
			SYNTAX	INTEGER
			MAX-ACCESS	read-only
			STATUS	current
			::= { hmWanMbus06 27 }

hmWanMbus06VIF0B		OBJECT-TYPE
			SYNTAX	INTEGER
			MAX-ACCESS	read-only
			STATUS	current
			::= { hmWanMbus06 28 }

hmWanMbus06Value0B		OBJECT-TYPE
			SYNTAX	INTEGER
			MAX-ACCESS	read-only
			STATUS	current
			::= { hmWanMbus06 29 }

hmWanMbus06VIF0C		OBJECT-TYPE
			SYNTAX	INTEGER
			MAX-ACCESS	read-only
			STATUS	current
			::= { hmWanMbus06 30 }

hmWanMbus06Value0C		OBJECT-TYPE
			SYNTAX	INTEGER
			MAX-ACCESS	read-only
			STATUS	current
			::= { hmWanMbus06 31 }

hmWanMbus06VIF0D		OBJECT-TYPE
			SYNTAX	INTEGER
			MAX-ACCESS	read-only
			STATUS	current
			::= { hmWanMbus06 32 }

hmWanMbus06Value0D		OBJECT-TYPE
			SYNTAX	INTEGER
			MAX-ACCESS	read-only
			STATUS	current
			::= { hmWanMbus06 33 }

hmWanMbus06VIF0E		OBJECT-TYPE
			SYNTAX	INTEGER
			MAX-ACCESS	read-only
			STATUS	current
			::= { hmWanMbus06 34 }

hmWanMbus06Value0E		OBJECT-TYPE
			SYNTAX	INTEGER
			MAX-ACCESS	read-only
			STATUS	current
			::= { hmWanMbus06 35 }

hmWanMbus06VIF0F		OBJECT-TYPE
			SYNTAX	INTEGER
			MAX-ACCESS	read-only
			STATUS	current
			::= { hmWanMbus06 36 }

hmWanMbus06Value0F		OBJECT-TYPE
			SYNTAX	INTEGER
			MAX-ACCESS	read-only
			STATUS	current
			::= { hmWanMbus06 37 }

hmWanMbus06VIF10		OBJECT-TYPE
			SYNTAX	INTEGER
			MAX-ACCESS	read-only
			STATUS	current
			::= { hmWanMbus06 38 }

hmWanMbus06Value10		OBJECT-TYPE
			SYNTAX	INTEGER
			MAX-ACCESS	read-only
			STATUS	current
			::= { hmWanMbus06 39 }

hmWanMbus06VIF11		OBJECT-TYPE
			SYNTAX	INTEGER
			MAX-ACCESS	read-only
			STATUS	current
			::= { hmWanMbus06 40 }

hmWanMbus06Value11		OBJECT-TYPE
			SYNTAX	INTEGER
			MAX-ACCESS	read-only
			STATUS	current
			::= { hmWanMbus06 41 }

hmWanMbus06VIF12		OBJECT-TYPE
			SYNTAX	INTEGER
			MAX-ACCESS	read-only
			STATUS	current
			::= { hmWanMbus06 42 }

hmWanMbus06Value12		OBJECT-TYPE
			SYNTAX	INTEGER
			MAX-ACCESS	read-only
			STATUS	current
			::= { hmWanMbus06 43 }

hmWanMbus06VIF13		OBJECT-TYPE
			SYNTAX	INTEGER
			MAX-ACCESS	read-only
			STATUS	current
			::= { hmWanMbus06 44 }

hmWanMbus06Value13		OBJECT-TYPE
			SYNTAX	INTEGER
			MAX-ACCESS	read-only
			STATUS	current
			::= { hmWanMbus06 45 }

hmWanMbus06VIF14		OBJECT-TYPE
			SYNTAX	INTEGER
			MAX-ACCESS	read-only
			STATUS	current
			::= { hmWanMbus06 46 }

hmWanMbus06Value14		OBJECT-TYPE
			SYNTAX	INTEGER
			MAX-ACCESS	read-only
			STATUS	current
			::= { hmWanMbus06 47 }

hmWanMbus06VIF15		OBJECT-TYPE
			SYNTAX	INTEGER
			MAX-ACCESS	read-only
			STATUS	current
			::= { hmWanMbus06 48 }

hmWanMbus06Value15		OBJECT-TYPE
			SYNTAX	INTEGER
			MAX-ACCESS	read-only
			STATUS	current
			::= { hmWanMbus06 49 }

hmWanMbus06VIF16		OBJECT-TYPE
			SYNTAX	INTEGER
			MAX-ACCESS	read-only
			STATUS	current
			::= { hmWanMbus06 50 }

hmWanMbus06Value16		OBJECT-TYPE
			SYNTAX	INTEGER
			MAX-ACCESS	read-only
			STATUS	current
			::= { hmWanMbus06 51 }

hmWanMbus06VIF17		OBJECT-TYPE
			SYNTAX	INTEGER
			MAX-ACCESS	read-only
			STATUS	current
			::= { hmWanMbus06 52 }

hmWanMbus06Value17		OBJECT-TYPE
			SYNTAX	INTEGER
			MAX-ACCESS	read-only
			STATUS	current
			::= { hmWanMbus06 53 }

hmWanMbus06VIF18		OBJECT-TYPE
			SYNTAX	INTEGER
			MAX-ACCESS	read-only
			STATUS	current
			::= { hmWanMbus06 54 }

hmWanMbus06Value18		OBJECT-TYPE
			SYNTAX	INTEGER
			MAX-ACCESS	read-only
			STATUS	current
			::= { hmWanMbus06 55 }

hmWanMbus06VIF19		OBJECT-TYPE
			SYNTAX	INTEGER
			MAX-ACCESS	read-only
			STATUS	current
			::= { hmWanMbus06 56 }

hmWanMbus06Value19		OBJECT-TYPE
			SYNTAX	INTEGER
			MAX-ACCESS	read-only
			STATUS	current
			::= { hmWanMbus06 57 }

hmWanMbus06VIF1A		OBJECT-TYPE
			SYNTAX	INTEGER
			MAX-ACCESS	read-only
			STATUS	current
			::= { hmWanMbus06 58 }

hmWanMbus06Value1A		OBJECT-TYPE
			SYNTAX	INTEGER
			MAX-ACCESS	read-only
			STATUS	current
			::= { hmWanMbus06 59 }

hmWanMbus06VIF1B		OBJECT-TYPE
			SYNTAX	INTEGER
			MAX-ACCESS	read-only
			STATUS	current
			::= { hmWanMbus06 60 }

hmWanMbus06Value1B		OBJECT-TYPE
			SYNTAX	INTEGER
			MAX-ACCESS	read-only
			STATUS	current
			::= { hmWanMbus06 61 }

hmWanMbus06VIF1C		OBJECT-TYPE
			SYNTAX	INTEGER
			MAX-ACCESS	read-only
			STATUS	current
			::= { hmWanMbus06 62 }

hmWanMbus06Value1C		OBJECT-TYPE
			SYNTAX	INTEGER
			MAX-ACCESS	read-only
			STATUS	current
			::= { hmWanMbus06 63 }

hmWanMbus06VIF1D		OBJECT-TYPE
			SYNTAX	INTEGER
			MAX-ACCESS	read-only
			STATUS	current
			::= { hmWanMbus06 64 }

hmWanMbus06Value1D		OBJECT-TYPE
			SYNTAX	INTEGER
			MAX-ACCESS	read-only
			STATUS	current
			::= { hmWanMbus06 65 }

hmWanMbus06VIF1E		OBJECT-TYPE
			SYNTAX	INTEGER
			MAX-ACCESS	read-only
			STATUS	current
			::= { hmWanMbus06 66 }

hmWanMbus06Value1E		OBJECT-TYPE
			SYNTAX	INTEGER
			MAX-ACCESS	read-only
			STATUS	current
			::= { hmWanMbus06 67 }

hmWanMbus06VIF1F		OBJECT-TYPE
			SYNTAX	INTEGER
			MAX-ACCESS	read-only
			STATUS	current
			::= { hmWanMbus06 68 }

hmWanMbus06Value1F		OBJECT-TYPE
			SYNTAX	INTEGER
			MAX-ACCESS	read-only
			STATUS	current
			::= { hmWanMbus06 69 }

hmWanMbus06VIF20		OBJECT-TYPE
			SYNTAX	INTEGER
			MAX-ACCESS	read-only
			STATUS	current
			::= { hmWanMbus06 70 }

hmWanMbus06Value20		OBJECT-TYPE
			SYNTAX	INTEGER
			MAX-ACCESS	read-only
			STATUS	current
			::= { hmWanMbus06 71 }

hmWanMbus06VIF21		OBJECT-TYPE
			SYNTAX	INTEGER
			MAX-ACCESS	read-only
			STATUS	current
			::= { hmWanMbus06 72 }

hmWanMbus06Value21		OBJECT-TYPE
			SYNTAX	INTEGER
			MAX-ACCESS	read-only
			STATUS	current
			::= { hmWanMbus06 73 }

hmWanMbus06VIF22		OBJECT-TYPE
			SYNTAX	INTEGER
			MAX-ACCESS	read-only
			STATUS	current
			::= { hmWanMbus06 74 }

hmWanMbus06Value22		OBJECT-TYPE
			SYNTAX	INTEGER
			MAX-ACCESS	read-only
			STATUS	current
			::= { hmWanMbus06 75 }

hmWanMbus06VIF23		OBJECT-TYPE
			SYNTAX	INTEGER
			MAX-ACCESS	read-only
			STATUS	current
			::= { hmWanMbus06 76 }

hmWanMbus06Value23		OBJECT-TYPE
			SYNTAX	INTEGER
			MAX-ACCESS	read-only
			STATUS	current
			::= { hmWanMbus06 77 }

hmWanMbus06VIF24		OBJECT-TYPE
			SYNTAX	INTEGER
			MAX-ACCESS	read-only
			STATUS	current
			::= { hmWanMbus06 78 }

hmWanMbus06Value24		OBJECT-TYPE
			SYNTAX	INTEGER
			MAX-ACCESS	read-only
			STATUS	current
			::= { hmWanMbus06 79 }

hmWanMbus06VIF25		OBJECT-TYPE
			SYNTAX	INTEGER
			MAX-ACCESS	read-only
			STATUS	current
			::= { hmWanMbus06 80 }

hmWanMbus06Value25		OBJECT-TYPE
			SYNTAX	INTEGER
			MAX-ACCESS	read-only
			STATUS	current
			::= { hmWanMbus06 81 }

hmWanMbus06VIF26		OBJECT-TYPE
			SYNTAX	INTEGER
			MAX-ACCESS	read-only
			STATUS	current
			::= { hmWanMbus06 82 }

hmWanMbus06Value26		OBJECT-TYPE
			SYNTAX	INTEGER
			MAX-ACCESS	read-only
			STATUS	current
			::= { hmWanMbus06 83 }

hmWanMbus06VIF27		OBJECT-TYPE
			SYNTAX	INTEGER
			MAX-ACCESS	read-only
			STATUS	current
			::= { hmWanMbus06 84 }

hmWanMbus06Value27		OBJECT-TYPE
			SYNTAX	INTEGER
			MAX-ACCESS	read-only
			STATUS	current
			::= { hmWanMbus06 85 }

hmWanMbus06VIF28		OBJECT-TYPE
			SYNTAX	INTEGER
			MAX-ACCESS	read-only
			STATUS	current
			::= { hmWanMbus06 86 }

hmWanMbus06Value28		OBJECT-TYPE
			SYNTAX	INTEGER
			MAX-ACCESS	read-only
			STATUS	current
			::= { hmWanMbus06 87 }

hmWanMbus06VIF29		OBJECT-TYPE
			SYNTAX	INTEGER
			MAX-ACCESS	read-only
			STATUS	current
			::= { hmWanMbus06 88 }

hmWanMbus06Value29		OBJECT-TYPE
			SYNTAX	INTEGER
			MAX-ACCESS	read-only
			STATUS	current
			::= { hmWanMbus06 89 }

hmWanMbus06VIF2A		OBJECT-TYPE
			SYNTAX	INTEGER
			MAX-ACCESS	read-only
			STATUS	current
			::= { hmWanMbus06 90 }

hmWanMbus06Value2A		OBJECT-TYPE
			SYNTAX	INTEGER
			MAX-ACCESS	read-only
			STATUS	current
			::= { hmWanMbus06 91 }

hmWanMbus06VIF2B		OBJECT-TYPE
			SYNTAX	INTEGER
			MAX-ACCESS	read-only
			STATUS	current
			::= { hmWanMbus06 92 }

hmWanMbus06Value2B		OBJECT-TYPE
			SYNTAX	INTEGER
			MAX-ACCESS	read-only
			STATUS	current
			::= { hmWanMbus06 93 }

hmWanMbus06VIF2C		OBJECT-TYPE
			SYNTAX	INTEGER
			MAX-ACCESS	read-only
			STATUS	current
			::= { hmWanMbus06 94 }

hmWanMbus06Value2C		OBJECT-TYPE
			SYNTAX	INTEGER
			MAX-ACCESS	read-only
			STATUS	current
			::= { hmWanMbus06 95 }

hmWanMbus06VIF2D		OBJECT-TYPE
			SYNTAX	INTEGER
			MAX-ACCESS	read-only
			STATUS	current
			::= { hmWanMbus06 96 }

hmWanMbus06Value2D		OBJECT-TYPE
			SYNTAX	INTEGER
			MAX-ACCESS	read-only
			STATUS	current
			::= { hmWanMbus06 97 }

hmWanMbus06VIF2E		OBJECT-TYPE
			SYNTAX	INTEGER
			MAX-ACCESS	read-only
			STATUS	current
			::= { hmWanMbus06 98 }

hmWanMbus06Value2E		OBJECT-TYPE
			SYNTAX	INTEGER
			MAX-ACCESS	read-only
			STATUS	current
			::= { hmWanMbus06 99 }

hmWanMbus06VIF2F		OBJECT-TYPE
			SYNTAX	INTEGER
			MAX-ACCESS	read-only
			STATUS	current
			::= { hmWanMbus06 100 }

hmWanMbus06Value2F		OBJECT-TYPE
			SYNTAX	INTEGER
			MAX-ACCESS	read-only
			STATUS	current
			::= { hmWanMbus06 101 }

hmWanMbus07			OBJECT IDENTIFIER ::= { hmWanMbus 7 }

hmWanMbus07IdNumber		OBJECT-TYPE
			SYNTAX	Gauge32
			MAX-ACCESS	read-only
			STATUS	current
			::= { hmWanMbus07 1 }

hmWanMbus07Manufacturer	OBJECT-TYPE
			SYNTAX	Gauge32
			MAX-ACCESS	read-only
			STATUS	current
			::= { hmWanMbus07 2 }

hmWanMbus07Version		OBJECT-TYPE
			SYNTAX	Gauge32
			MAX-ACCESS	read-only
			STATUS	current
			::= { hmWanMbus07 3 }

hmWanMbus07Medium		OBJECT-TYPE
			SYNTAX	Gauge32
			MAX-ACCESS	read-only
			STATUS	current
			::= { hmWanMbus07 4 }

hmWanMbus07Status		OBJECT-TYPE
			SYNTAX	Gauge32
			MAX-ACCESS	read-only
			STATUS	current
			::= { hmWanMbus07 5 }

hmWanMbus07VIF00		OBJECT-TYPE
			SYNTAX	INTEGER
			MAX-ACCESS	read-only
			STATUS	current
			::= { hmWanMbus07 6 }

hmWanMbus07Value00		OBJECT-TYPE
			SYNTAX	INTEGER
			MAX-ACCESS	read-only
			STATUS	current
			::= { hmWanMbus07 7 }

hmWanMbus07VIF01		OBJECT-TYPE
			SYNTAX	INTEGER
			MAX-ACCESS	read-only
			STATUS	current
			::= { hmWanMbus07 8 }

hmWanMbus07Value01		OBJECT-TYPE
			SYNTAX	INTEGER
			MAX-ACCESS	read-only
			STATUS	current
			::= { hmWanMbus07 9 }

hmWanMbus07VIF02		OBJECT-TYPE
			SYNTAX	INTEGER
			MAX-ACCESS	read-only
			STATUS	current
			::= { hmWanMbus07 10 }

hmWanMbus07Value02		OBJECT-TYPE
			SYNTAX	INTEGER
			MAX-ACCESS	read-only
			STATUS	current
			::= { hmWanMbus07 11 }

hmWanMbus07VIF03		OBJECT-TYPE
			SYNTAX	INTEGER
			MAX-ACCESS	read-only
			STATUS	current
			::= { hmWanMbus07 12 }

hmWanMbus07Value03		OBJECT-TYPE
			SYNTAX	INTEGER
			MAX-ACCESS	read-only
			STATUS	current
			::= { hmWanMbus07 13 }

hmWanMbus07VIF04		OBJECT-TYPE
			SYNTAX	INTEGER
			MAX-ACCESS	read-only
			STATUS	current
			::= { hmWanMbus07 14 }

hmWanMbus07Value04		OBJECT-TYPE
			SYNTAX	INTEGER
			MAX-ACCESS	read-only
			STATUS	current
			::= { hmWanMbus07 15 }

hmWanMbus07VIF05		OBJECT-TYPE
			SYNTAX	INTEGER
			MAX-ACCESS	read-only
			STATUS	current
			::= { hmWanMbus07 16 }

hmWanMbus07Value05		OBJECT-TYPE
			SYNTAX	INTEGER
			MAX-ACCESS	read-only
			STATUS	current
			::= { hmWanMbus07 17 }

hmWanMbus07VIF06		OBJECT-TYPE
			SYNTAX	INTEGER
			MAX-ACCESS	read-only
			STATUS	current
			::= { hmWanMbus07 18 }

hmWanMbus07Value06		OBJECT-TYPE
			SYNTAX	INTEGER
			MAX-ACCESS	read-only
			STATUS	current
			::= { hmWanMbus07 19 }

hmWanMbus07VIF07		OBJECT-TYPE
			SYNTAX	INTEGER
			MAX-ACCESS	read-only
			STATUS	current
			::= { hmWanMbus07 20 }

hmWanMbus07Value07		OBJECT-TYPE
			SYNTAX	INTEGER
			MAX-ACCESS	read-only
			STATUS	current
			::= { hmWanMbus07 21 }

hmWanMbus07VIF08		OBJECT-TYPE
			SYNTAX	INTEGER
			MAX-ACCESS	read-only
			STATUS	current
			::= { hmWanMbus07 22 }

hmWanMbus07Value08		OBJECT-TYPE
			SYNTAX	INTEGER
			MAX-ACCESS	read-only
			STATUS	current
			::= { hmWanMbus07 23 }

hmWanMbus07VIF09		OBJECT-TYPE
			SYNTAX	INTEGER
			MAX-ACCESS	read-only
			STATUS	current
			::= { hmWanMbus07 24 }

hmWanMbus07Value09		OBJECT-TYPE
			SYNTAX	INTEGER
			MAX-ACCESS	read-only
			STATUS	current
			::= { hmWanMbus07 25 }

hmWanMbus07VIF0A		OBJECT-TYPE
			SYNTAX	INTEGER
			MAX-ACCESS	read-only
			STATUS	current
			::= { hmWanMbus07 26 }

hmWanMbus07Value0A		OBJECT-TYPE
			SYNTAX	INTEGER
			MAX-ACCESS	read-only
			STATUS	current
			::= { hmWanMbus07 27 }

hmWanMbus07VIF0B		OBJECT-TYPE
			SYNTAX	INTEGER
			MAX-ACCESS	read-only
			STATUS	current
			::= { hmWanMbus07 28 }

hmWanMbus07Value0B		OBJECT-TYPE
			SYNTAX	INTEGER
			MAX-ACCESS	read-only
			STATUS	current
			::= { hmWanMbus07 29 }

hmWanMbus07VIF0C		OBJECT-TYPE
			SYNTAX	INTEGER
			MAX-ACCESS	read-only
			STATUS	current
			::= { hmWanMbus07 30 }

hmWanMbus07Value0C		OBJECT-TYPE
			SYNTAX	INTEGER
			MAX-ACCESS	read-only
			STATUS	current
			::= { hmWanMbus07 31 }

hmWanMbus07VIF0D		OBJECT-TYPE
			SYNTAX	INTEGER
			MAX-ACCESS	read-only
			STATUS	current
			::= { hmWanMbus07 32 }

hmWanMbus07Value0D		OBJECT-TYPE
			SYNTAX	INTEGER
			MAX-ACCESS	read-only
			STATUS	current
			::= { hmWanMbus07 33 }

hmWanMbus07VIF0E		OBJECT-TYPE
			SYNTAX	INTEGER
			MAX-ACCESS	read-only
			STATUS	current
			::= { hmWanMbus07 34 }

hmWanMbus07Value0E		OBJECT-TYPE
			SYNTAX	INTEGER
			MAX-ACCESS	read-only
			STATUS	current
			::= { hmWanMbus07 35 }

hmWanMbus07VIF0F		OBJECT-TYPE
			SYNTAX	INTEGER
			MAX-ACCESS	read-only
			STATUS	current
			::= { hmWanMbus07 36 }

hmWanMbus07Value0F		OBJECT-TYPE
			SYNTAX	INTEGER
			MAX-ACCESS	read-only
			STATUS	current
			::= { hmWanMbus07 37 }

hmWanMbus07VIF10		OBJECT-TYPE
			SYNTAX	INTEGER
			MAX-ACCESS	read-only
			STATUS	current
			::= { hmWanMbus07 38 }

hmWanMbus07Value10		OBJECT-TYPE
			SYNTAX	INTEGER
			MAX-ACCESS	read-only
			STATUS	current
			::= { hmWanMbus07 39 }

hmWanMbus07VIF11		OBJECT-TYPE
			SYNTAX	INTEGER
			MAX-ACCESS	read-only
			STATUS	current
			::= { hmWanMbus07 40 }

hmWanMbus07Value11		OBJECT-TYPE
			SYNTAX	INTEGER
			MAX-ACCESS	read-only
			STATUS	current
			::= { hmWanMbus07 41 }

hmWanMbus07VIF12		OBJECT-TYPE
			SYNTAX	INTEGER
			MAX-ACCESS	read-only
			STATUS	current
			::= { hmWanMbus07 42 }

hmWanMbus07Value12		OBJECT-TYPE
			SYNTAX	INTEGER
			MAX-ACCESS	read-only
			STATUS	current
			::= { hmWanMbus07 43 }

hmWanMbus07VIF13		OBJECT-TYPE
			SYNTAX	INTEGER
			MAX-ACCESS	read-only
			STATUS	current
			::= { hmWanMbus07 44 }

hmWanMbus07Value13		OBJECT-TYPE
			SYNTAX	INTEGER
			MAX-ACCESS	read-only
			STATUS	current
			::= { hmWanMbus07 45 }

hmWanMbus07VIF14		OBJECT-TYPE
			SYNTAX	INTEGER
			MAX-ACCESS	read-only
			STATUS	current
			::= { hmWanMbus07 46 }

hmWanMbus07Value14		OBJECT-TYPE
			SYNTAX	INTEGER
			MAX-ACCESS	read-only
			STATUS	current
			::= { hmWanMbus07 47 }

hmWanMbus07VIF15		OBJECT-TYPE
			SYNTAX	INTEGER
			MAX-ACCESS	read-only
			STATUS	current
			::= { hmWanMbus07 48 }

hmWanMbus07Value15		OBJECT-TYPE
			SYNTAX	INTEGER
			MAX-ACCESS	read-only
			STATUS	current
			::= { hmWanMbus07 49 }

hmWanMbus07VIF16		OBJECT-TYPE
			SYNTAX	INTEGER
			MAX-ACCESS	read-only
			STATUS	current
			::= { hmWanMbus07 50 }

hmWanMbus07Value16		OBJECT-TYPE
			SYNTAX	INTEGER
			MAX-ACCESS	read-only
			STATUS	current
			::= { hmWanMbus07 51 }

hmWanMbus07VIF17		OBJECT-TYPE
			SYNTAX	INTEGER
			MAX-ACCESS	read-only
			STATUS	current
			::= { hmWanMbus07 52 }

hmWanMbus07Value17		OBJECT-TYPE
			SYNTAX	INTEGER
			MAX-ACCESS	read-only
			STATUS	current
			::= { hmWanMbus07 53 }

hmWanMbus07VIF18		OBJECT-TYPE
			SYNTAX	INTEGER
			MAX-ACCESS	read-only
			STATUS	current
			::= { hmWanMbus07 54 }

hmWanMbus07Value18		OBJECT-TYPE
			SYNTAX	INTEGER
			MAX-ACCESS	read-only
			STATUS	current
			::= { hmWanMbus07 55 }

hmWanMbus07VIF19		OBJECT-TYPE
			SYNTAX	INTEGER
			MAX-ACCESS	read-only
			STATUS	current
			::= { hmWanMbus07 56 }

hmWanMbus07Value19		OBJECT-TYPE
			SYNTAX	INTEGER
			MAX-ACCESS	read-only
			STATUS	current
			::= { hmWanMbus07 57 }

hmWanMbus07VIF1A		OBJECT-TYPE
			SYNTAX	INTEGER
			MAX-ACCESS	read-only
			STATUS	current
			::= { hmWanMbus07 58 }

hmWanMbus07Value1A		OBJECT-TYPE
			SYNTAX	INTEGER
			MAX-ACCESS	read-only
			STATUS	current
			::= { hmWanMbus07 59 }

hmWanMbus07VIF1B		OBJECT-TYPE
			SYNTAX	INTEGER
			MAX-ACCESS	read-only
			STATUS	current
			::= { hmWanMbus07 60 }

hmWanMbus07Value1B		OBJECT-TYPE
			SYNTAX	INTEGER
			MAX-ACCESS	read-only
			STATUS	current
			::= { hmWanMbus07 61 }

hmWanMbus07VIF1C		OBJECT-TYPE
			SYNTAX	INTEGER
			MAX-ACCESS	read-only
			STATUS	current
			::= { hmWanMbus07 62 }

hmWanMbus07Value1C		OBJECT-TYPE
			SYNTAX	INTEGER
			MAX-ACCESS	read-only
			STATUS	current
			::= { hmWanMbus07 63 }

hmWanMbus07VIF1D		OBJECT-TYPE
			SYNTAX	INTEGER
			MAX-ACCESS	read-only
			STATUS	current
			::= { hmWanMbus07 64 }

hmWanMbus07Value1D		OBJECT-TYPE
			SYNTAX	INTEGER
			MAX-ACCESS	read-only
			STATUS	current
			::= { hmWanMbus07 65 }

hmWanMbus07VIF1E		OBJECT-TYPE
			SYNTAX	INTEGER
			MAX-ACCESS	read-only
			STATUS	current
			::= { hmWanMbus07 66 }

hmWanMbus07Value1E		OBJECT-TYPE
			SYNTAX	INTEGER
			MAX-ACCESS	read-only
			STATUS	current
			::= { hmWanMbus07 67 }

hmWanMbus07VIF1F		OBJECT-TYPE
			SYNTAX	INTEGER
			MAX-ACCESS	read-only
			STATUS	current
			::= { hmWanMbus07 68 }

hmWanMbus07Value1F		OBJECT-TYPE
			SYNTAX	INTEGER
			MAX-ACCESS	read-only
			STATUS	current
			::= { hmWanMbus07 69 }

hmWanMbus07VIF20		OBJECT-TYPE
			SYNTAX	INTEGER
			MAX-ACCESS	read-only
			STATUS	current
			::= { hmWanMbus07 70 }

hmWanMbus07Value20		OBJECT-TYPE
			SYNTAX	INTEGER
			MAX-ACCESS	read-only
			STATUS	current
			::= { hmWanMbus07 71 }

hmWanMbus07VIF21		OBJECT-TYPE
			SYNTAX	INTEGER
			MAX-ACCESS	read-only
			STATUS	current
			::= { hmWanMbus07 72 }

hmWanMbus07Value21		OBJECT-TYPE
			SYNTAX	INTEGER
			MAX-ACCESS	read-only
			STATUS	current
			::= { hmWanMbus07 73 }

hmWanMbus07VIF22		OBJECT-TYPE
			SYNTAX	INTEGER
			MAX-ACCESS	read-only
			STATUS	current
			::= { hmWanMbus07 74 }

hmWanMbus07Value22		OBJECT-TYPE
			SYNTAX	INTEGER
			MAX-ACCESS	read-only
			STATUS	current
			::= { hmWanMbus07 75 }

hmWanMbus07VIF23		OBJECT-TYPE
			SYNTAX	INTEGER
			MAX-ACCESS	read-only
			STATUS	current
			::= { hmWanMbus07 76 }

hmWanMbus07Value23		OBJECT-TYPE
			SYNTAX	INTEGER
			MAX-ACCESS	read-only
			STATUS	current
			::= { hmWanMbus07 77 }

hmWanMbus07VIF24		OBJECT-TYPE
			SYNTAX	INTEGER
			MAX-ACCESS	read-only
			STATUS	current
			::= { hmWanMbus07 78 }

hmWanMbus07Value24		OBJECT-TYPE
			SYNTAX	INTEGER
			MAX-ACCESS	read-only
			STATUS	current
			::= { hmWanMbus07 79 }

hmWanMbus07VIF25		OBJECT-TYPE
			SYNTAX	INTEGER
			MAX-ACCESS	read-only
			STATUS	current
			::= { hmWanMbus07 80 }

hmWanMbus07Value25		OBJECT-TYPE
			SYNTAX	INTEGER
			MAX-ACCESS	read-only
			STATUS	current
			::= { hmWanMbus07 81 }

hmWanMbus07VIF26		OBJECT-TYPE
			SYNTAX	INTEGER
			MAX-ACCESS	read-only
			STATUS	current
			::= { hmWanMbus07 82 }

hmWanMbus07Value26		OBJECT-TYPE
			SYNTAX	INTEGER
			MAX-ACCESS	read-only
			STATUS	current
			::= { hmWanMbus07 83 }

hmWanMbus07VIF27		OBJECT-TYPE
			SYNTAX	INTEGER
			MAX-ACCESS	read-only
			STATUS	current
			::= { hmWanMbus07 84 }

hmWanMbus07Value27		OBJECT-TYPE
			SYNTAX	INTEGER
			MAX-ACCESS	read-only
			STATUS	current
			::= { hmWanMbus07 85 }

hmWanMbus07VIF28		OBJECT-TYPE
			SYNTAX	INTEGER
			MAX-ACCESS	read-only
			STATUS	current
			::= { hmWanMbus07 86 }

hmWanMbus07Value28		OBJECT-TYPE
			SYNTAX	INTEGER
			MAX-ACCESS	read-only
			STATUS	current
			::= { hmWanMbus07 87 }

hmWanMbus07VIF29		OBJECT-TYPE
			SYNTAX	INTEGER
			MAX-ACCESS	read-only
			STATUS	current
			::= { hmWanMbus07 88 }

hmWanMbus07Value29		OBJECT-TYPE
			SYNTAX	INTEGER
			MAX-ACCESS	read-only
			STATUS	current
			::= { hmWanMbus07 89 }

hmWanMbus07VIF2A		OBJECT-TYPE
			SYNTAX	INTEGER
			MAX-ACCESS	read-only
			STATUS	current
			::= { hmWanMbus07 90 }

hmWanMbus07Value2A		OBJECT-TYPE
			SYNTAX	INTEGER
			MAX-ACCESS	read-only
			STATUS	current
			::= { hmWanMbus07 91 }

hmWanMbus07VIF2B		OBJECT-TYPE
			SYNTAX	INTEGER
			MAX-ACCESS	read-only
			STATUS	current
			::= { hmWanMbus07 92 }

hmWanMbus07Value2B		OBJECT-TYPE
			SYNTAX	INTEGER
			MAX-ACCESS	read-only
			STATUS	current
			::= { hmWanMbus07 93 }

hmWanMbus07VIF2C		OBJECT-TYPE
			SYNTAX	INTEGER
			MAX-ACCESS	read-only
			STATUS	current
			::= { hmWanMbus07 94 }

hmWanMbus07Value2C		OBJECT-TYPE
			SYNTAX	INTEGER
			MAX-ACCESS	read-only
			STATUS	current
			::= { hmWanMbus07 95 }

hmWanMbus07VIF2D		OBJECT-TYPE
			SYNTAX	INTEGER
			MAX-ACCESS	read-only
			STATUS	current
			::= { hmWanMbus07 96 }

hmWanMbus07Value2D		OBJECT-TYPE
			SYNTAX	INTEGER
			MAX-ACCESS	read-only
			STATUS	current
			::= { hmWanMbus07 97 }

hmWanMbus07VIF2E		OBJECT-TYPE
			SYNTAX	INTEGER
			MAX-ACCESS	read-only
			STATUS	current
			::= { hmWanMbus07 98 }

hmWanMbus07Value2E		OBJECT-TYPE
			SYNTAX	INTEGER
			MAX-ACCESS	read-only
			STATUS	current
			::= { hmWanMbus07 99 }

hmWanMbus07VIF2F		OBJECT-TYPE
			SYNTAX	INTEGER
			MAX-ACCESS	read-only
			STATUS	current
			::= { hmWanMbus07 100 }

hmWanMbus07Value2F		OBJECT-TYPE
			SYNTAX	INTEGER
			MAX-ACCESS	read-only
			STATUS	current
			::= { hmWanMbus07 101 }

hmWanMbus08			OBJECT IDENTIFIER ::= { hmWanMbus 8 }

hmWanMbus08IdNumber		OBJECT-TYPE
			SYNTAX	Gauge32
			MAX-ACCESS	read-only
			STATUS	current
			::= { hmWanMbus08 1 }

hmWanMbus08Manufacturer	OBJECT-TYPE
			SYNTAX	Gauge32
			MAX-ACCESS	read-only
			STATUS	current
			::= { hmWanMbus08 2 }

hmWanMbus08Version		OBJECT-TYPE
			SYNTAX	Gauge32
			MAX-ACCESS	read-only
			STATUS	current
			::= { hmWanMbus08 3 }

hmWanMbus08Medium		OBJECT-TYPE
			SYNTAX	Gauge32
			MAX-ACCESS	read-only
			STATUS	current
			::= { hmWanMbus08 4 }

hmWanMbus08Status		OBJECT-TYPE
			SYNTAX	Gauge32
			MAX-ACCESS	read-only
			STATUS	current
			::= { hmWanMbus08 5 }

hmWanMbus08VIF00		OBJECT-TYPE
			SYNTAX	INTEGER
			MAX-ACCESS	read-only
			STATUS	current
			::= { hmWanMbus08 6 }

hmWanMbus08Value00		OBJECT-TYPE
			SYNTAX	INTEGER
			MAX-ACCESS	read-only
			STATUS	current
			::= { hmWanMbus08 7 }

hmWanMbus08VIF01		OBJECT-TYPE
			SYNTAX	INTEGER
			MAX-ACCESS	read-only
			STATUS	current
			::= { hmWanMbus08 8 }

hmWanMbus08Value01		OBJECT-TYPE
			SYNTAX	INTEGER
			MAX-ACCESS	read-only
			STATUS	current
			::= { hmWanMbus08 9 }

hmWanMbus08VIF02		OBJECT-TYPE
			SYNTAX	INTEGER
			MAX-ACCESS	read-only
			STATUS	current
			::= { hmWanMbus08 10 }

hmWanMbus08Value02		OBJECT-TYPE
			SYNTAX	INTEGER
			MAX-ACCESS	read-only
			STATUS	current
			::= { hmWanMbus08 11 }

hmWanMbus08VIF03		OBJECT-TYPE
			SYNTAX	INTEGER
			MAX-ACCESS	read-only
			STATUS	current
			::= { hmWanMbus08 12 }

hmWanMbus08Value03		OBJECT-TYPE
			SYNTAX	INTEGER
			MAX-ACCESS	read-only
			STATUS	current
			::= { hmWanMbus08 13 }

hmWanMbus08VIF04		OBJECT-TYPE
			SYNTAX	INTEGER
			MAX-ACCESS	read-only
			STATUS	current
			::= { hmWanMbus08 14 }

hmWanMbus08Value04		OBJECT-TYPE
			SYNTAX	INTEGER
			MAX-ACCESS	read-only
			STATUS	current
			::= { hmWanMbus08 15 }

hmWanMbus08VIF05		OBJECT-TYPE
			SYNTAX	INTEGER
			MAX-ACCESS	read-only
			STATUS	current
			::= { hmWanMbus08 16 }

hmWanMbus08Value05		OBJECT-TYPE
			SYNTAX	INTEGER
			MAX-ACCESS	read-only
			STATUS	current
			::= { hmWanMbus08 17 }

hmWanMbus08VIF06		OBJECT-TYPE
			SYNTAX	INTEGER
			MAX-ACCESS	read-only
			STATUS	current
			::= { hmWanMbus08 18 }

hmWanMbus08Value06		OBJECT-TYPE
			SYNTAX	INTEGER
			MAX-ACCESS	read-only
			STATUS	current
			::= { hmWanMbus08 19 }

hmWanMbus08VIF07		OBJECT-TYPE
			SYNTAX	INTEGER
			MAX-ACCESS	read-only
			STATUS	current
			::= { hmWanMbus08 20 }

hmWanMbus08Value07		OBJECT-TYPE
			SYNTAX	INTEGER
			MAX-ACCESS	read-only
			STATUS	current
			::= { hmWanMbus08 21 }

hmWanMbus08VIF08		OBJECT-TYPE
			SYNTAX	INTEGER
			MAX-ACCESS	read-only
			STATUS	current
			::= { hmWanMbus08 22 }

hmWanMbus08Value08		OBJECT-TYPE
			SYNTAX	INTEGER
			MAX-ACCESS	read-only
			STATUS	current
			::= { hmWanMbus08 23 }

hmWanMbus08VIF09		OBJECT-TYPE
			SYNTAX	INTEGER
			MAX-ACCESS	read-only
			STATUS	current
			::= { hmWanMbus08 24 }

hmWanMbus08Value09		OBJECT-TYPE
			SYNTAX	INTEGER
			MAX-ACCESS	read-only
			STATUS	current
			::= { hmWanMbus08 25 }

hmWanMbus08VIF0A		OBJECT-TYPE
			SYNTAX	INTEGER
			MAX-ACCESS	read-only
			STATUS	current
			::= { hmWanMbus08 26 }

hmWanMbus08Value0A		OBJECT-TYPE
			SYNTAX	INTEGER
			MAX-ACCESS	read-only
			STATUS	current
			::= { hmWanMbus08 27 }

hmWanMbus08VIF0B		OBJECT-TYPE
			SYNTAX	INTEGER
			MAX-ACCESS	read-only
			STATUS	current
			::= { hmWanMbus08 28 }

hmWanMbus08Value0B		OBJECT-TYPE
			SYNTAX	INTEGER
			MAX-ACCESS	read-only
			STATUS	current
			::= { hmWanMbus08 29 }

hmWanMbus08VIF0C		OBJECT-TYPE
			SYNTAX	INTEGER
			MAX-ACCESS	read-only
			STATUS	current
			::= { hmWanMbus08 30 }

hmWanMbus08Value0C		OBJECT-TYPE
			SYNTAX	INTEGER
			MAX-ACCESS	read-only
			STATUS	current
			::= { hmWanMbus08 31 }

hmWanMbus08VIF0D		OBJECT-TYPE
			SYNTAX	INTEGER
			MAX-ACCESS	read-only
			STATUS	current
			::= { hmWanMbus08 32 }

hmWanMbus08Value0D		OBJECT-TYPE
			SYNTAX	INTEGER
			MAX-ACCESS	read-only
			STATUS	current
			::= { hmWanMbus08 33 }

hmWanMbus08VIF0E		OBJECT-TYPE
			SYNTAX	INTEGER
			MAX-ACCESS	read-only
			STATUS	current
			::= { hmWanMbus08 34 }

hmWanMbus08Value0E		OBJECT-TYPE
			SYNTAX	INTEGER
			MAX-ACCESS	read-only
			STATUS	current
			::= { hmWanMbus08 35 }

hmWanMbus08VIF0F		OBJECT-TYPE
			SYNTAX	INTEGER
			MAX-ACCESS	read-only
			STATUS	current
			::= { hmWanMbus08 36 }

hmWanMbus08Value0F		OBJECT-TYPE
			SYNTAX	INTEGER
			MAX-ACCESS	read-only
			STATUS	current
			::= { hmWanMbus08 37 }

hmWanMbus08VIF10		OBJECT-TYPE
			SYNTAX	INTEGER
			MAX-ACCESS	read-only
			STATUS	current
			::= { hmWanMbus08 38 }

hmWanMbus08Value10		OBJECT-TYPE
			SYNTAX	INTEGER
			MAX-ACCESS	read-only
			STATUS	current
			::= { hmWanMbus08 39 }

hmWanMbus08VIF11		OBJECT-TYPE
			SYNTAX	INTEGER
			MAX-ACCESS	read-only
			STATUS	current
			::= { hmWanMbus08 40 }

hmWanMbus08Value11		OBJECT-TYPE
			SYNTAX	INTEGER
			MAX-ACCESS	read-only
			STATUS	current
			::= { hmWanMbus08 41 }

hmWanMbus08VIF12		OBJECT-TYPE
			SYNTAX	INTEGER
			MAX-ACCESS	read-only
			STATUS	current
			::= { hmWanMbus08 42 }

hmWanMbus08Value12		OBJECT-TYPE
			SYNTAX	INTEGER
			MAX-ACCESS	read-only
			STATUS	current
			::= { hmWanMbus08 43 }

hmWanMbus08VIF13		OBJECT-TYPE
			SYNTAX	INTEGER
			MAX-ACCESS	read-only
			STATUS	current
			::= { hmWanMbus08 44 }

hmWanMbus08Value13		OBJECT-TYPE
			SYNTAX	INTEGER
			MAX-ACCESS	read-only
			STATUS	current
			::= { hmWanMbus08 45 }

hmWanMbus08VIF14		OBJECT-TYPE
			SYNTAX	INTEGER
			MAX-ACCESS	read-only
			STATUS	current
			::= { hmWanMbus08 46 }

hmWanMbus08Value14		OBJECT-TYPE
			SYNTAX	INTEGER
			MAX-ACCESS	read-only
			STATUS	current
			::= { hmWanMbus08 47 }

hmWanMbus08VIF15		OBJECT-TYPE
			SYNTAX	INTEGER
			MAX-ACCESS	read-only
			STATUS	current
			::= { hmWanMbus08 48 }

hmWanMbus08Value15		OBJECT-TYPE
			SYNTAX	INTEGER
			MAX-ACCESS	read-only
			STATUS	current
			::= { hmWanMbus08 49 }

hmWanMbus08VIF16		OBJECT-TYPE
			SYNTAX	INTEGER
			MAX-ACCESS	read-only
			STATUS	current
			::= { hmWanMbus08 50 }

hmWanMbus08Value16		OBJECT-TYPE
			SYNTAX	INTEGER
			MAX-ACCESS	read-only
			STATUS	current
			::= { hmWanMbus08 51 }

hmWanMbus08VIF17		OBJECT-TYPE
			SYNTAX	INTEGER
			MAX-ACCESS	read-only
			STATUS	current
			::= { hmWanMbus08 52 }

hmWanMbus08Value17		OBJECT-TYPE
			SYNTAX	INTEGER
			MAX-ACCESS	read-only
			STATUS	current
			::= { hmWanMbus08 53 }

hmWanMbus08VIF18		OBJECT-TYPE
			SYNTAX	INTEGER
			MAX-ACCESS	read-only
			STATUS	current
			::= { hmWanMbus08 54 }

hmWanMbus08Value18		OBJECT-TYPE
			SYNTAX	INTEGER
			MAX-ACCESS	read-only
			STATUS	current
			::= { hmWanMbus08 55 }

hmWanMbus08VIF19		OBJECT-TYPE
			SYNTAX	INTEGER
			MAX-ACCESS	read-only
			STATUS	current
			::= { hmWanMbus08 56 }

hmWanMbus08Value19		OBJECT-TYPE
			SYNTAX	INTEGER
			MAX-ACCESS	read-only
			STATUS	current
			::= { hmWanMbus08 57 }

hmWanMbus08VIF1A		OBJECT-TYPE
			SYNTAX	INTEGER
			MAX-ACCESS	read-only
			STATUS	current
			::= { hmWanMbus08 58 }

hmWanMbus08Value1A		OBJECT-TYPE
			SYNTAX	INTEGER
			MAX-ACCESS	read-only
			STATUS	current
			::= { hmWanMbus08 59 }

hmWanMbus08VIF1B		OBJECT-TYPE
			SYNTAX	INTEGER
			MAX-ACCESS	read-only
			STATUS	current
			::= { hmWanMbus08 60 }

hmWanMbus08Value1B		OBJECT-TYPE
			SYNTAX	INTEGER
			MAX-ACCESS	read-only
			STATUS	current
			::= { hmWanMbus08 61 }

hmWanMbus08VIF1C		OBJECT-TYPE
			SYNTAX	INTEGER
			MAX-ACCESS	read-only
			STATUS	current
			::= { hmWanMbus08 62 }

hmWanMbus08Value1C		OBJECT-TYPE
			SYNTAX	INTEGER
			MAX-ACCESS	read-only
			STATUS	current
			::= { hmWanMbus08 63 }

hmWanMbus08VIF1D		OBJECT-TYPE
			SYNTAX	INTEGER
			MAX-ACCESS	read-only
			STATUS	current
			::= { hmWanMbus08 64 }

hmWanMbus08Value1D		OBJECT-TYPE
			SYNTAX	INTEGER
			MAX-ACCESS	read-only
			STATUS	current
			::= { hmWanMbus08 65 }

hmWanMbus08VIF1E		OBJECT-TYPE
			SYNTAX	INTEGER
			MAX-ACCESS	read-only
			STATUS	current
			::= { hmWanMbus08 66 }

hmWanMbus08Value1E		OBJECT-TYPE
			SYNTAX	INTEGER
			MAX-ACCESS	read-only
			STATUS	current
			::= { hmWanMbus08 67 }

hmWanMbus08VIF1F		OBJECT-TYPE
			SYNTAX	INTEGER
			MAX-ACCESS	read-only
			STATUS	current
			::= { hmWanMbus08 68 }

hmWanMbus08Value1F		OBJECT-TYPE
			SYNTAX	INTEGER
			MAX-ACCESS	read-only
			STATUS	current
			::= { hmWanMbus08 69 }

hmWanMbus08VIF20		OBJECT-TYPE
			SYNTAX	INTEGER
			MAX-ACCESS	read-only
			STATUS	current
			::= { hmWanMbus08 70 }

hmWanMbus08Value20		OBJECT-TYPE
			SYNTAX	INTEGER
			MAX-ACCESS	read-only
			STATUS	current
			::= { hmWanMbus08 71 }

hmWanMbus08VIF21		OBJECT-TYPE
			SYNTAX	INTEGER
			MAX-ACCESS	read-only
			STATUS	current
			::= { hmWanMbus08 72 }

hmWanMbus08Value21		OBJECT-TYPE
			SYNTAX	INTEGER
			MAX-ACCESS	read-only
			STATUS	current
			::= { hmWanMbus08 73 }

hmWanMbus08VIF22		OBJECT-TYPE
			SYNTAX	INTEGER
			MAX-ACCESS	read-only
			STATUS	current
			::= { hmWanMbus08 74 }

hmWanMbus08Value22		OBJECT-TYPE
			SYNTAX	INTEGER
			MAX-ACCESS	read-only
			STATUS	current
			::= { hmWanMbus08 75 }

hmWanMbus08VIF23		OBJECT-TYPE
			SYNTAX	INTEGER
			MAX-ACCESS	read-only
			STATUS	current
			::= { hmWanMbus08 76 }

hmWanMbus08Value23		OBJECT-TYPE
			SYNTAX	INTEGER
			MAX-ACCESS	read-only
			STATUS	current
			::= { hmWanMbus08 77 }

hmWanMbus08VIF24		OBJECT-TYPE
			SYNTAX	INTEGER
			MAX-ACCESS	read-only
			STATUS	current
			::= { hmWanMbus08 78 }

hmWanMbus08Value24		OBJECT-TYPE
			SYNTAX	INTEGER
			MAX-ACCESS	read-only
			STATUS	current
			::= { hmWanMbus08 79 }

hmWanMbus08VIF25		OBJECT-TYPE
			SYNTAX	INTEGER
			MAX-ACCESS	read-only
			STATUS	current
			::= { hmWanMbus08 80 }

hmWanMbus08Value25		OBJECT-TYPE
			SYNTAX	INTEGER
			MAX-ACCESS	read-only
			STATUS	current
			::= { hmWanMbus08 81 }

hmWanMbus08VIF26		OBJECT-TYPE
			SYNTAX	INTEGER
			MAX-ACCESS	read-only
			STATUS	current
			::= { hmWanMbus08 82 }

hmWanMbus08Value26		OBJECT-TYPE
			SYNTAX	INTEGER
			MAX-ACCESS	read-only
			STATUS	current
			::= { hmWanMbus08 83 }

hmWanMbus08VIF27		OBJECT-TYPE
			SYNTAX	INTEGER
			MAX-ACCESS	read-only
			STATUS	current
			::= { hmWanMbus08 84 }

hmWanMbus08Value27		OBJECT-TYPE
			SYNTAX	INTEGER
			MAX-ACCESS	read-only
			STATUS	current
			::= { hmWanMbus08 85 }

hmWanMbus08VIF28		OBJECT-TYPE
			SYNTAX	INTEGER
			MAX-ACCESS	read-only
			STATUS	current
			::= { hmWanMbus08 86 }

hmWanMbus08Value28		OBJECT-TYPE
			SYNTAX	INTEGER
			MAX-ACCESS	read-only
			STATUS	current
			::= { hmWanMbus08 87 }

hmWanMbus08VIF29		OBJECT-TYPE
			SYNTAX	INTEGER
			MAX-ACCESS	read-only
			STATUS	current
			::= { hmWanMbus08 88 }

hmWanMbus08Value29		OBJECT-TYPE
			SYNTAX	INTEGER
			MAX-ACCESS	read-only
			STATUS	current
			::= { hmWanMbus08 89 }

hmWanMbus08VIF2A		OBJECT-TYPE
			SYNTAX	INTEGER
			MAX-ACCESS	read-only
			STATUS	current
			::= { hmWanMbus08 90 }

hmWanMbus08Value2A		OBJECT-TYPE
			SYNTAX	INTEGER
			MAX-ACCESS	read-only
			STATUS	current
			::= { hmWanMbus08 91 }

hmWanMbus08VIF2B		OBJECT-TYPE
			SYNTAX	INTEGER
			MAX-ACCESS	read-only
			STATUS	current
			::= { hmWanMbus08 92 }

hmWanMbus08Value2B		OBJECT-TYPE
			SYNTAX	INTEGER
			MAX-ACCESS	read-only
			STATUS	current
			::= { hmWanMbus08 93 }

hmWanMbus08VIF2C		OBJECT-TYPE
			SYNTAX	INTEGER
			MAX-ACCESS	read-only
			STATUS	current
			::= { hmWanMbus08 94 }

hmWanMbus08Value2C		OBJECT-TYPE
			SYNTAX	INTEGER
			MAX-ACCESS	read-only
			STATUS	current
			::= { hmWanMbus08 95 }

hmWanMbus08VIF2D		OBJECT-TYPE
			SYNTAX	INTEGER
			MAX-ACCESS	read-only
			STATUS	current
			::= { hmWanMbus08 96 }

hmWanMbus08Value2D		OBJECT-TYPE
			SYNTAX	INTEGER
			MAX-ACCESS	read-only
			STATUS	current
			::= { hmWanMbus08 97 }

hmWanMbus08VIF2E		OBJECT-TYPE
			SYNTAX	INTEGER
			MAX-ACCESS	read-only
			STATUS	current
			::= { hmWanMbus08 98 }

hmWanMbus08Value2E		OBJECT-TYPE
			SYNTAX	INTEGER
			MAX-ACCESS	read-only
			STATUS	current
			::= { hmWanMbus08 99 }

hmWanMbus08VIF2F		OBJECT-TYPE
			SYNTAX	INTEGER
			MAX-ACCESS	read-only
			STATUS	current
			::= { hmWanMbus08 100 }

hmWanMbus08Value2F		OBJECT-TYPE
			SYNTAX	INTEGER
			MAX-ACCESS	read-only
			STATUS	current
			::= { hmWanMbus08 101 }

hmWanMbus09			OBJECT IDENTIFIER ::= { hmWanMbus 9 }

hmWanMbus09IdNumber		OBJECT-TYPE
			SYNTAX	Gauge32
			MAX-ACCESS	read-only
			STATUS	current
			::= { hmWanMbus09 1 }

hmWanMbus09Manufacturer	OBJECT-TYPE
			SYNTAX	Gauge32
			MAX-ACCESS	read-only
			STATUS	current
			::= { hmWanMbus09 2 }

hmWanMbus09Version		OBJECT-TYPE
			SYNTAX	Gauge32
			MAX-ACCESS	read-only
			STATUS	current
			::= { hmWanMbus09 3 }

hmWanMbus09Medium		OBJECT-TYPE
			SYNTAX	Gauge32
			MAX-ACCESS	read-only
			STATUS	current
			::= { hmWanMbus09 4 }

hmWanMbus09Status		OBJECT-TYPE
			SYNTAX	Gauge32
			MAX-ACCESS	read-only
			STATUS	current
			::= { hmWanMbus09 5 }

hmWanMbus09VIF00		OBJECT-TYPE
			SYNTAX	INTEGER
			MAX-ACCESS	read-only
			STATUS	current
			::= { hmWanMbus09 6 }

hmWanMbus09Value00		OBJECT-TYPE
			SYNTAX	INTEGER
			MAX-ACCESS	read-only
			STATUS	current
			::= { hmWanMbus09 7 }

hmWanMbus09VIF01		OBJECT-TYPE
			SYNTAX	INTEGER
			MAX-ACCESS	read-only
			STATUS	current
			::= { hmWanMbus09 8 }

hmWanMbus09Value01		OBJECT-TYPE
			SYNTAX	INTEGER
			MAX-ACCESS	read-only
			STATUS	current
			::= { hmWanMbus09 9 }

hmWanMbus09VIF02		OBJECT-TYPE
			SYNTAX	INTEGER
			MAX-ACCESS	read-only
			STATUS	current
			::= { hmWanMbus09 10 }

hmWanMbus09Value02		OBJECT-TYPE
			SYNTAX	INTEGER
			MAX-ACCESS	read-only
			STATUS	current
			::= { hmWanMbus09 11 }

hmWanMbus09VIF03		OBJECT-TYPE
			SYNTAX	INTEGER
			MAX-ACCESS	read-only
			STATUS	current
			::= { hmWanMbus09 12 }

hmWanMbus09Value03		OBJECT-TYPE
			SYNTAX	INTEGER
			MAX-ACCESS	read-only
			STATUS	current
			::= { hmWanMbus09 13 }

hmWanMbus09VIF04		OBJECT-TYPE
			SYNTAX	INTEGER
			MAX-ACCESS	read-only
			STATUS	current
			::= { hmWanMbus09 14 }

hmWanMbus09Value04		OBJECT-TYPE
			SYNTAX	INTEGER
			MAX-ACCESS	read-only
			STATUS	current
			::= { hmWanMbus09 15 }

hmWanMbus09VIF05		OBJECT-TYPE
			SYNTAX	INTEGER
			MAX-ACCESS	read-only
			STATUS	current
			::= { hmWanMbus09 16 }

hmWanMbus09Value05		OBJECT-TYPE
			SYNTAX	INTEGER
			MAX-ACCESS	read-only
			STATUS	current
			::= { hmWanMbus09 17 }

hmWanMbus09VIF06		OBJECT-TYPE
			SYNTAX	INTEGER
			MAX-ACCESS	read-only
			STATUS	current
			::= { hmWanMbus09 18 }

hmWanMbus09Value06		OBJECT-TYPE
			SYNTAX	INTEGER
			MAX-ACCESS	read-only
			STATUS	current
			::= { hmWanMbus09 19 }

hmWanMbus09VIF07		OBJECT-TYPE
			SYNTAX	INTEGER
			MAX-ACCESS	read-only
			STATUS	current
			::= { hmWanMbus09 20 }

hmWanMbus09Value07		OBJECT-TYPE
			SYNTAX	INTEGER
			MAX-ACCESS	read-only
			STATUS	current
			::= { hmWanMbus09 21 }

hmWanMbus09VIF08		OBJECT-TYPE
			SYNTAX	INTEGER
			MAX-ACCESS	read-only
			STATUS	current
			::= { hmWanMbus09 22 }

hmWanMbus09Value08		OBJECT-TYPE
			SYNTAX	INTEGER
			MAX-ACCESS	read-only
			STATUS	current
			::= { hmWanMbus09 23 }

hmWanMbus09VIF09		OBJECT-TYPE
			SYNTAX	INTEGER
			MAX-ACCESS	read-only
			STATUS	current
			::= { hmWanMbus09 24 }

hmWanMbus09Value09		OBJECT-TYPE
			SYNTAX	INTEGER
			MAX-ACCESS	read-only
			STATUS	current
			::= { hmWanMbus09 25 }

hmWanMbus09VIF0A		OBJECT-TYPE
			SYNTAX	INTEGER
			MAX-ACCESS	read-only
			STATUS	current
			::= { hmWanMbus09 26 }

hmWanMbus09Value0A		OBJECT-TYPE
			SYNTAX	INTEGER
			MAX-ACCESS	read-only
			STATUS	current
			::= { hmWanMbus09 27 }

hmWanMbus09VIF0B		OBJECT-TYPE
			SYNTAX	INTEGER
			MAX-ACCESS	read-only
			STATUS	current
			::= { hmWanMbus09 28 }

hmWanMbus09Value0B		OBJECT-TYPE
			SYNTAX	INTEGER
			MAX-ACCESS	read-only
			STATUS	current
			::= { hmWanMbus09 29 }

hmWanMbus09VIF0C		OBJECT-TYPE
			SYNTAX	INTEGER
			MAX-ACCESS	read-only
			STATUS	current
			::= { hmWanMbus09 30 }

hmWanMbus09Value0C		OBJECT-TYPE
			SYNTAX	INTEGER
			MAX-ACCESS	read-only
			STATUS	current
			::= { hmWanMbus09 31 }

hmWanMbus09VIF0D		OBJECT-TYPE
			SYNTAX	INTEGER
			MAX-ACCESS	read-only
			STATUS	current
			::= { hmWanMbus09 32 }

hmWanMbus09Value0D		OBJECT-TYPE
			SYNTAX	INTEGER
			MAX-ACCESS	read-only
			STATUS	current
			::= { hmWanMbus09 33 }

hmWanMbus09VIF0E		OBJECT-TYPE
			SYNTAX	INTEGER
			MAX-ACCESS	read-only
			STATUS	current
			::= { hmWanMbus09 34 }

hmWanMbus09Value0E		OBJECT-TYPE
			SYNTAX	INTEGER
			MAX-ACCESS	read-only
			STATUS	current
			::= { hmWanMbus09 35 }

hmWanMbus09VIF0F		OBJECT-TYPE
			SYNTAX	INTEGER
			MAX-ACCESS	read-only
			STATUS	current
			::= { hmWanMbus09 36 }

hmWanMbus09Value0F		OBJECT-TYPE
			SYNTAX	INTEGER
			MAX-ACCESS	read-only
			STATUS	current
			::= { hmWanMbus09 37 }

hmWanMbus09VIF10		OBJECT-TYPE
			SYNTAX	INTEGER
			MAX-ACCESS	read-only
			STATUS	current
			::= { hmWanMbus09 38 }

hmWanMbus09Value10		OBJECT-TYPE
			SYNTAX	INTEGER
			MAX-ACCESS	read-only
			STATUS	current
			::= { hmWanMbus09 39 }

hmWanMbus09VIF11		OBJECT-TYPE
			SYNTAX	INTEGER
			MAX-ACCESS	read-only
			STATUS	current
			::= { hmWanMbus09 40 }

hmWanMbus09Value11		OBJECT-TYPE
			SYNTAX	INTEGER
			MAX-ACCESS	read-only
			STATUS	current
			::= { hmWanMbus09 41 }

hmWanMbus09VIF12		OBJECT-TYPE
			SYNTAX	INTEGER
			MAX-ACCESS	read-only
			STATUS	current
			::= { hmWanMbus09 42 }

hmWanMbus09Value12		OBJECT-TYPE
			SYNTAX	INTEGER
			MAX-ACCESS	read-only
			STATUS	current
			::= { hmWanMbus09 43 }

hmWanMbus09VIF13		OBJECT-TYPE
			SYNTAX	INTEGER
			MAX-ACCESS	read-only
			STATUS	current
			::= { hmWanMbus09 44 }

hmWanMbus09Value13		OBJECT-TYPE
			SYNTAX	INTEGER
			MAX-ACCESS	read-only
			STATUS	current
			::= { hmWanMbus09 45 }

hmWanMbus09VIF14		OBJECT-TYPE
			SYNTAX	INTEGER
			MAX-ACCESS	read-only
			STATUS	current
			::= { hmWanMbus09 46 }

hmWanMbus09Value14		OBJECT-TYPE
			SYNTAX	INTEGER
			MAX-ACCESS	read-only
			STATUS	current
			::= { hmWanMbus09 47 }

hmWanMbus09VIF15		OBJECT-TYPE
			SYNTAX	INTEGER
			MAX-ACCESS	read-only
			STATUS	current
			::= { hmWanMbus09 48 }

hmWanMbus09Value15		OBJECT-TYPE
			SYNTAX	INTEGER
			MAX-ACCESS	read-only
			STATUS	current
			::= { hmWanMbus09 49 }

hmWanMbus09VIF16		OBJECT-TYPE
			SYNTAX	INTEGER
			MAX-ACCESS	read-only
			STATUS	current
			::= { hmWanMbus09 50 }

hmWanMbus09Value16		OBJECT-TYPE
			SYNTAX	INTEGER
			MAX-ACCESS	read-only
			STATUS	current
			::= { hmWanMbus09 51 }

hmWanMbus09VIF17		OBJECT-TYPE
			SYNTAX	INTEGER
			MAX-ACCESS	read-only
			STATUS	current
			::= { hmWanMbus09 52 }

hmWanMbus09Value17		OBJECT-TYPE
			SYNTAX	INTEGER
			MAX-ACCESS	read-only
			STATUS	current
			::= { hmWanMbus09 53 }

hmWanMbus09VIF18		OBJECT-TYPE
			SYNTAX	INTEGER
			MAX-ACCESS	read-only
			STATUS	current
			::= { hmWanMbus09 54 }

hmWanMbus09Value18		OBJECT-TYPE
			SYNTAX	INTEGER
			MAX-ACCESS	read-only
			STATUS	current
			::= { hmWanMbus09 55 }

hmWanMbus09VIF19		OBJECT-TYPE
			SYNTAX	INTEGER
			MAX-ACCESS	read-only
			STATUS	current
			::= { hmWanMbus09 56 }

hmWanMbus09Value19		OBJECT-TYPE
			SYNTAX	INTEGER
			MAX-ACCESS	read-only
			STATUS	current
			::= { hmWanMbus09 57 }

hmWanMbus09VIF1A		OBJECT-TYPE
			SYNTAX	INTEGER
			MAX-ACCESS	read-only
			STATUS	current
			::= { hmWanMbus09 58 }

hmWanMbus09Value1A		OBJECT-TYPE
			SYNTAX	INTEGER
			MAX-ACCESS	read-only
			STATUS	current
			::= { hmWanMbus09 59 }

hmWanMbus09VIF1B		OBJECT-TYPE
			SYNTAX	INTEGER
			MAX-ACCESS	read-only
			STATUS	current
			::= { hmWanMbus09 60 }

hmWanMbus09Value1B		OBJECT-TYPE
			SYNTAX	INTEGER
			MAX-ACCESS	read-only
			STATUS	current
			::= { hmWanMbus09 61 }

hmWanMbus09VIF1C		OBJECT-TYPE
			SYNTAX	INTEGER
			MAX-ACCESS	read-only
			STATUS	current
			::= { hmWanMbus09 62 }

hmWanMbus09Value1C		OBJECT-TYPE
			SYNTAX	INTEGER
			MAX-ACCESS	read-only
			STATUS	current
			::= { hmWanMbus09 63 }

hmWanMbus09VIF1D		OBJECT-TYPE
			SYNTAX	INTEGER
			MAX-ACCESS	read-only
			STATUS	current
			::= { hmWanMbus09 64 }

hmWanMbus09Value1D		OBJECT-TYPE
			SYNTAX	INTEGER
			MAX-ACCESS	read-only
			STATUS	current
			::= { hmWanMbus09 65 }

hmWanMbus09VIF1E		OBJECT-TYPE
			SYNTAX	INTEGER
			MAX-ACCESS	read-only
			STATUS	current
			::= { hmWanMbus09 66 }

hmWanMbus09Value1E		OBJECT-TYPE
			SYNTAX	INTEGER
			MAX-ACCESS	read-only
			STATUS	current
			::= { hmWanMbus09 67 }

hmWanMbus09VIF1F		OBJECT-TYPE
			SYNTAX	INTEGER
			MAX-ACCESS	read-only
			STATUS	current
			::= { hmWanMbus09 68 }

hmWanMbus09Value1F		OBJECT-TYPE
			SYNTAX	INTEGER
			MAX-ACCESS	read-only
			STATUS	current
			::= { hmWanMbus09 69 }

hmWanMbus09VIF20		OBJECT-TYPE
			SYNTAX	INTEGER
			MAX-ACCESS	read-only
			STATUS	current
			::= { hmWanMbus09 70 }

hmWanMbus09Value20		OBJECT-TYPE
			SYNTAX	INTEGER
			MAX-ACCESS	read-only
			STATUS	current
			::= { hmWanMbus09 71 }

hmWanMbus09VIF21		OBJECT-TYPE
			SYNTAX	INTEGER
			MAX-ACCESS	read-only
			STATUS	current
			::= { hmWanMbus09 72 }

hmWanMbus09Value21		OBJECT-TYPE
			SYNTAX	INTEGER
			MAX-ACCESS	read-only
			STATUS	current
			::= { hmWanMbus09 73 }

hmWanMbus09VIF22		OBJECT-TYPE
			SYNTAX	INTEGER
			MAX-ACCESS	read-only
			STATUS	current
			::= { hmWanMbus09 74 }

hmWanMbus09Value22		OBJECT-TYPE
			SYNTAX	INTEGER
			MAX-ACCESS	read-only
			STATUS	current
			::= { hmWanMbus09 75 }

hmWanMbus09VIF23		OBJECT-TYPE
			SYNTAX	INTEGER
			MAX-ACCESS	read-only
			STATUS	current
			::= { hmWanMbus09 76 }

hmWanMbus09Value23		OBJECT-TYPE
			SYNTAX	INTEGER
			MAX-ACCESS	read-only
			STATUS	current
			::= { hmWanMbus09 77 }

hmWanMbus09VIF24		OBJECT-TYPE
			SYNTAX	INTEGER
			MAX-ACCESS	read-only
			STATUS	current
			::= { hmWanMbus09 78 }

hmWanMbus09Value24		OBJECT-TYPE
			SYNTAX	INTEGER
			MAX-ACCESS	read-only
			STATUS	current
			::= { hmWanMbus09 79 }

hmWanMbus09VIF25		OBJECT-TYPE
			SYNTAX	INTEGER
			MAX-ACCESS	read-only
			STATUS	current
			::= { hmWanMbus09 80 }

hmWanMbus09Value25		OBJECT-TYPE
			SYNTAX	INTEGER
			MAX-ACCESS	read-only
			STATUS	current
			::= { hmWanMbus09 81 }

hmWanMbus09VIF26		OBJECT-TYPE
			SYNTAX	INTEGER
			MAX-ACCESS	read-only
			STATUS	current
			::= { hmWanMbus09 82 }

hmWanMbus09Value26		OBJECT-TYPE
			SYNTAX	INTEGER
			MAX-ACCESS	read-only
			STATUS	current
			::= { hmWanMbus09 83 }

hmWanMbus09VIF27		OBJECT-TYPE
			SYNTAX	INTEGER
			MAX-ACCESS	read-only
			STATUS	current
			::= { hmWanMbus09 84 }

hmWanMbus09Value27		OBJECT-TYPE
			SYNTAX	INTEGER
			MAX-ACCESS	read-only
			STATUS	current
			::= { hmWanMbus09 85 }

hmWanMbus09VIF28		OBJECT-TYPE
			SYNTAX	INTEGER
			MAX-ACCESS	read-only
			STATUS	current
			::= { hmWanMbus09 86 }

hmWanMbus09Value28		OBJECT-TYPE
			SYNTAX	INTEGER
			MAX-ACCESS	read-only
			STATUS	current
			::= { hmWanMbus09 87 }

hmWanMbus09VIF29		OBJECT-TYPE
			SYNTAX	INTEGER
			MAX-ACCESS	read-only
			STATUS	current
			::= { hmWanMbus09 88 }

hmWanMbus09Value29		OBJECT-TYPE
			SYNTAX	INTEGER
			MAX-ACCESS	read-only
			STATUS	current
			::= { hmWanMbus09 89 }

hmWanMbus09VIF2A		OBJECT-TYPE
			SYNTAX	INTEGER
			MAX-ACCESS	read-only
			STATUS	current
			::= { hmWanMbus09 90 }

hmWanMbus09Value2A		OBJECT-TYPE
			SYNTAX	INTEGER
			MAX-ACCESS	read-only
			STATUS	current
			::= { hmWanMbus09 91 }

hmWanMbus09VIF2B		OBJECT-TYPE
			SYNTAX	INTEGER
			MAX-ACCESS	read-only
			STATUS	current
			::= { hmWanMbus09 92 }

hmWanMbus09Value2B		OBJECT-TYPE
			SYNTAX	INTEGER
			MAX-ACCESS	read-only
			STATUS	current
			::= { hmWanMbus09 93 }

hmWanMbus09VIF2C		OBJECT-TYPE
			SYNTAX	INTEGER
			MAX-ACCESS	read-only
			STATUS	current
			::= { hmWanMbus09 94 }

hmWanMbus09Value2C		OBJECT-TYPE
			SYNTAX	INTEGER
			MAX-ACCESS	read-only
			STATUS	current
			::= { hmWanMbus09 95 }

hmWanMbus09VIF2D		OBJECT-TYPE
			SYNTAX	INTEGER
			MAX-ACCESS	read-only
			STATUS	current
			::= { hmWanMbus09 96 }

hmWanMbus09Value2D		OBJECT-TYPE
			SYNTAX	INTEGER
			MAX-ACCESS	read-only
			STATUS	current
			::= { hmWanMbus09 97 }

hmWanMbus09VIF2E		OBJECT-TYPE
			SYNTAX	INTEGER
			MAX-ACCESS	read-only
			STATUS	current
			::= { hmWanMbus09 98 }

hmWanMbus09Value2E		OBJECT-TYPE
			SYNTAX	INTEGER
			MAX-ACCESS	read-only
			STATUS	current
			::= { hmWanMbus09 99 }

hmWanMbus09VIF2F		OBJECT-TYPE
			SYNTAX	INTEGER
			MAX-ACCESS	read-only
			STATUS	current
			::= { hmWanMbus09 100 }

hmWanMbus09Value2F		OBJECT-TYPE
			SYNTAX	INTEGER
			MAX-ACCESS	read-only
			STATUS	current
			::= { hmWanMbus09 101 }

hmWanMbus0A			OBJECT IDENTIFIER ::= { hmWanMbus 10 }

hmWanMbus0AIdNumber		OBJECT-TYPE
			SYNTAX	Gauge32
			MAX-ACCESS	read-only
			STATUS	current
			::= { hmWanMbus0A 1 }

hmWanMbus0AManufacturer	OBJECT-TYPE
			SYNTAX	Gauge32
			MAX-ACCESS	read-only
			STATUS	current
			::= { hmWanMbus0A 2 }

hmWanMbus0AVersion		OBJECT-TYPE
			SYNTAX	Gauge32
			MAX-ACCESS	read-only
			STATUS	current
			::= { hmWanMbus0A 3 }

hmWanMbus0AMedium		OBJECT-TYPE
			SYNTAX	Gauge32
			MAX-ACCESS	read-only
			STATUS	current
			::= { hmWanMbus0A 4 }

hmWanMbus0AStatus		OBJECT-TYPE
			SYNTAX	Gauge32
			MAX-ACCESS	read-only
			STATUS	current
			::= { hmWanMbus0A 5 }

hmWanMbus0AVIF00		OBJECT-TYPE
			SYNTAX	INTEGER
			MAX-ACCESS	read-only
			STATUS	current
			::= { hmWanMbus0A 6 }

hmWanMbus0AValue00		OBJECT-TYPE
			SYNTAX	INTEGER
			MAX-ACCESS	read-only
			STATUS	current
			::= { hmWanMbus0A 7 }

hmWanMbus0AVIF01		OBJECT-TYPE
			SYNTAX	INTEGER
			MAX-ACCESS	read-only
			STATUS	current
			::= { hmWanMbus0A 8 }

hmWanMbus0AValue01		OBJECT-TYPE
			SYNTAX	INTEGER
			MAX-ACCESS	read-only
			STATUS	current
			::= { hmWanMbus0A 9 }

hmWanMbus0AVIF02		OBJECT-TYPE
			SYNTAX	INTEGER
			MAX-ACCESS	read-only
			STATUS	current
			::= { hmWanMbus0A 10 }

hmWanMbus0AValue02		OBJECT-TYPE
			SYNTAX	INTEGER
			MAX-ACCESS	read-only
			STATUS	current
			::= { hmWanMbus0A 11 }

hmWanMbus0AVIF03		OBJECT-TYPE
			SYNTAX	INTEGER
			MAX-ACCESS	read-only
			STATUS	current
			::= { hmWanMbus0A 12 }

hmWanMbus0AValue03		OBJECT-TYPE
			SYNTAX	INTEGER
			MAX-ACCESS	read-only
			STATUS	current
			::= { hmWanMbus0A 13 }

hmWanMbus0AVIF04		OBJECT-TYPE
			SYNTAX	INTEGER
			MAX-ACCESS	read-only
			STATUS	current
			::= { hmWanMbus0A 14 }

hmWanMbus0AValue04		OBJECT-TYPE
			SYNTAX	INTEGER
			MAX-ACCESS	read-only
			STATUS	current
			::= { hmWanMbus0A 15 }

hmWanMbus0AVIF05		OBJECT-TYPE
			SYNTAX	INTEGER
			MAX-ACCESS	read-only
			STATUS	current
			::= { hmWanMbus0A 16 }

hmWanMbus0AValue05		OBJECT-TYPE
			SYNTAX	INTEGER
			MAX-ACCESS	read-only
			STATUS	current
			::= { hmWanMbus0A 17 }

hmWanMbus0AVIF06		OBJECT-TYPE
			SYNTAX	INTEGER
			MAX-ACCESS	read-only
			STATUS	current
			::= { hmWanMbus0A 18 }

hmWanMbus0AValue06		OBJECT-TYPE
			SYNTAX	INTEGER
			MAX-ACCESS	read-only
			STATUS	current
			::= { hmWanMbus0A 19 }

hmWanMbus0AVIF07		OBJECT-TYPE
			SYNTAX	INTEGER
			MAX-ACCESS	read-only
			STATUS	current
			::= { hmWanMbus0A 20 }

hmWanMbus0AValue07		OBJECT-TYPE
			SYNTAX	INTEGER
			MAX-ACCESS	read-only
			STATUS	current
			::= { hmWanMbus0A 21 }

hmWanMbus0AVIF08		OBJECT-TYPE
			SYNTAX	INTEGER
			MAX-ACCESS	read-only
			STATUS	current
			::= { hmWanMbus0A 22 }

hmWanMbus0AValue08		OBJECT-TYPE
			SYNTAX	INTEGER
			MAX-ACCESS	read-only
			STATUS	current
			::= { hmWanMbus0A 23 }

hmWanMbus0AVIF09		OBJECT-TYPE
			SYNTAX	INTEGER
			MAX-ACCESS	read-only
			STATUS	current
			::= { hmWanMbus0A 24 }

hmWanMbus0AValue09		OBJECT-TYPE
			SYNTAX	INTEGER
			MAX-ACCESS	read-only
			STATUS	current
			::= { hmWanMbus0A 25 }

hmWanMbus0AVIF0A		OBJECT-TYPE
			SYNTAX	INTEGER
			MAX-ACCESS	read-only
			STATUS	current
			::= { hmWanMbus0A 26 }

hmWanMbus0AValue0A		OBJECT-TYPE
			SYNTAX	INTEGER
			MAX-ACCESS	read-only
			STATUS	current
			::= { hmWanMbus0A 27 }

hmWanMbus0AVIF0B		OBJECT-TYPE
			SYNTAX	INTEGER
			MAX-ACCESS	read-only
			STATUS	current
			::= { hmWanMbus0A 28 }

hmWanMbus0AValue0B		OBJECT-TYPE
			SYNTAX	INTEGER
			MAX-ACCESS	read-only
			STATUS	current
			::= { hmWanMbus0A 29 }

hmWanMbus0AVIF0C		OBJECT-TYPE
			SYNTAX	INTEGER
			MAX-ACCESS	read-only
			STATUS	current
			::= { hmWanMbus0A 30 }

hmWanMbus0AValue0C		OBJECT-TYPE
			SYNTAX	INTEGER
			MAX-ACCESS	read-only
			STATUS	current
			::= { hmWanMbus0A 31 }

hmWanMbus0AVIF0D		OBJECT-TYPE
			SYNTAX	INTEGER
			MAX-ACCESS	read-only
			STATUS	current
			::= { hmWanMbus0A 32 }

hmWanMbus0AValue0D		OBJECT-TYPE
			SYNTAX	INTEGER
			MAX-ACCESS	read-only
			STATUS	current
			::= { hmWanMbus0A 33 }

hmWanMbus0AVIF0E		OBJECT-TYPE
			SYNTAX	INTEGER
			MAX-ACCESS	read-only
			STATUS	current
			::= { hmWanMbus0A 34 }

hmWanMbus0AValue0E		OBJECT-TYPE
			SYNTAX	INTEGER
			MAX-ACCESS	read-only
			STATUS	current
			::= { hmWanMbus0A 35 }

hmWanMbus0AVIF0F		OBJECT-TYPE
			SYNTAX	INTEGER
			MAX-ACCESS	read-only
			STATUS	current
			::= { hmWanMbus0A 36 }

hmWanMbus0AValue0F		OBJECT-TYPE
			SYNTAX	INTEGER
			MAX-ACCESS	read-only
			STATUS	current
			::= { hmWanMbus0A 37 }

hmWanMbus0AVIF10		OBJECT-TYPE
			SYNTAX	INTEGER
			MAX-ACCESS	read-only
			STATUS	current
			::= { hmWanMbus0A 38 }

hmWanMbus0AValue10		OBJECT-TYPE
			SYNTAX	INTEGER
			MAX-ACCESS	read-only
			STATUS	current
			::= { hmWanMbus0A 39 }

hmWanMbus0AVIF11		OBJECT-TYPE
			SYNTAX	INTEGER
			MAX-ACCESS	read-only
			STATUS	current
			::= { hmWanMbus0A 40 }

hmWanMbus0AValue11		OBJECT-TYPE
			SYNTAX	INTEGER
			MAX-ACCESS	read-only
			STATUS	current
			::= { hmWanMbus0A 41 }

hmWanMbus0AVIF12		OBJECT-TYPE
			SYNTAX	INTEGER
			MAX-ACCESS	read-only
			STATUS	current
			::= { hmWanMbus0A 42 }

hmWanMbus0AValue12		OBJECT-TYPE
			SYNTAX	INTEGER
			MAX-ACCESS	read-only
			STATUS	current
			::= { hmWanMbus0A 43 }

hmWanMbus0AVIF13		OBJECT-TYPE
			SYNTAX	INTEGER
			MAX-ACCESS	read-only
			STATUS	current
			::= { hmWanMbus0A 44 }

hmWanMbus0AValue13		OBJECT-TYPE
			SYNTAX	INTEGER
			MAX-ACCESS	read-only
			STATUS	current
			::= { hmWanMbus0A 45 }

hmWanMbus0AVIF14		OBJECT-TYPE
			SYNTAX	INTEGER
			MAX-ACCESS	read-only
			STATUS	current
			::= { hmWanMbus0A 46 }

hmWanMbus0AValue14		OBJECT-TYPE
			SYNTAX	INTEGER
			MAX-ACCESS	read-only
			STATUS	current
			::= { hmWanMbus0A 47 }

hmWanMbus0AVIF15		OBJECT-TYPE
			SYNTAX	INTEGER
			MAX-ACCESS	read-only
			STATUS	current
			::= { hmWanMbus0A 48 }

hmWanMbus0AValue15		OBJECT-TYPE
			SYNTAX	INTEGER
			MAX-ACCESS	read-only
			STATUS	current
			::= { hmWanMbus0A 49 }

hmWanMbus0AVIF16		OBJECT-TYPE
			SYNTAX	INTEGER
			MAX-ACCESS	read-only
			STATUS	current
			::= { hmWanMbus0A 50 }

hmWanMbus0AValue16		OBJECT-TYPE
			SYNTAX	INTEGER
			MAX-ACCESS	read-only
			STATUS	current
			::= { hmWanMbus0A 51 }

hmWanMbus0AVIF17		OBJECT-TYPE
			SYNTAX	INTEGER
			MAX-ACCESS	read-only
			STATUS	current
			::= { hmWanMbus0A 52 }

hmWanMbus0AValue17		OBJECT-TYPE
			SYNTAX	INTEGER
			MAX-ACCESS	read-only
			STATUS	current
			::= { hmWanMbus0A 53 }

hmWanMbus0AVIF18		OBJECT-TYPE
			SYNTAX	INTEGER
			MAX-ACCESS	read-only
			STATUS	current
			::= { hmWanMbus0A 54 }

hmWanMbus0AValue18		OBJECT-TYPE
			SYNTAX	INTEGER
			MAX-ACCESS	read-only
			STATUS	current
			::= { hmWanMbus0A 55 }

hmWanMbus0AVIF19		OBJECT-TYPE
			SYNTAX	INTEGER
			MAX-ACCESS	read-only
			STATUS	current
			::= { hmWanMbus0A 56 }

hmWanMbus0AValue19		OBJECT-TYPE
			SYNTAX	INTEGER
			MAX-ACCESS	read-only
			STATUS	current
			::= { hmWanMbus0A 57 }

hmWanMbus0AVIF1A		OBJECT-TYPE
			SYNTAX	INTEGER
			MAX-ACCESS	read-only
			STATUS	current
			::= { hmWanMbus0A 58 }

hmWanMbus0AValue1A		OBJECT-TYPE
			SYNTAX	INTEGER
			MAX-ACCESS	read-only
			STATUS	current
			::= { hmWanMbus0A 59 }

hmWanMbus0AVIF1B		OBJECT-TYPE
			SYNTAX	INTEGER
			MAX-ACCESS	read-only
			STATUS	current
			::= { hmWanMbus0A 60 }

hmWanMbus0AValue1B		OBJECT-TYPE
			SYNTAX	INTEGER
			MAX-ACCESS	read-only
			STATUS	current
			::= { hmWanMbus0A 61 }

hmWanMbus0AVIF1C		OBJECT-TYPE
			SYNTAX	INTEGER
			MAX-ACCESS	read-only
			STATUS	current
			::= { hmWanMbus0A 62 }

hmWanMbus0AValue1C		OBJECT-TYPE
			SYNTAX	INTEGER
			MAX-ACCESS	read-only
			STATUS	current
			::= { hmWanMbus0A 63 }

hmWanMbus0AVIF1D		OBJECT-TYPE
			SYNTAX	INTEGER
			MAX-ACCESS	read-only
			STATUS	current
			::= { hmWanMbus0A 64 }

hmWanMbus0AValue1D		OBJECT-TYPE
			SYNTAX	INTEGER
			MAX-ACCESS	read-only
			STATUS	current
			::= { hmWanMbus0A 65 }

hmWanMbus0AVIF1E		OBJECT-TYPE
			SYNTAX	INTEGER
			MAX-ACCESS	read-only
			STATUS	current
			::= { hmWanMbus0A 66 }

hmWanMbus0AValue1E		OBJECT-TYPE
			SYNTAX	INTEGER
			MAX-ACCESS	read-only
			STATUS	current
			::= { hmWanMbus0A 67 }

hmWanMbus0AVIF1F		OBJECT-TYPE
			SYNTAX	INTEGER
			MAX-ACCESS	read-only
			STATUS	current
			::= { hmWanMbus0A 68 }

hmWanMbus0AValue1F		OBJECT-TYPE
			SYNTAX	INTEGER
			MAX-ACCESS	read-only
			STATUS	current
			::= { hmWanMbus0A 69 }

hmWanMbus0AVIF20		OBJECT-TYPE
			SYNTAX	INTEGER
			MAX-ACCESS	read-only
			STATUS	current
			::= { hmWanMbus0A 70 }

hmWanMbus0AValue20		OBJECT-TYPE
			SYNTAX	INTEGER
			MAX-ACCESS	read-only
			STATUS	current
			::= { hmWanMbus0A 71 }

hmWanMbus0AVIF21		OBJECT-TYPE
			SYNTAX	INTEGER
			MAX-ACCESS	read-only
			STATUS	current
			::= { hmWanMbus0A 72 }

hmWanMbus0AValue21		OBJECT-TYPE
			SYNTAX	INTEGER
			MAX-ACCESS	read-only
			STATUS	current
			::= { hmWanMbus0A 73 }

hmWanMbus0AVIF22		OBJECT-TYPE
			SYNTAX	INTEGER
			MAX-ACCESS	read-only
			STATUS	current
			::= { hmWanMbus0A 74 }

hmWanMbus0AValue22		OBJECT-TYPE
			SYNTAX	INTEGER
			MAX-ACCESS	read-only
			STATUS	current
			::= { hmWanMbus0A 75 }

hmWanMbus0AVIF23		OBJECT-TYPE
			SYNTAX	INTEGER
			MAX-ACCESS	read-only
			STATUS	current
			::= { hmWanMbus0A 76 }

hmWanMbus0AValue23		OBJECT-TYPE
			SYNTAX	INTEGER
			MAX-ACCESS	read-only
			STATUS	current
			::= { hmWanMbus0A 77 }

hmWanMbus0AVIF24		OBJECT-TYPE
			SYNTAX	INTEGER
			MAX-ACCESS	read-only
			STATUS	current
			::= { hmWanMbus0A 78 }

hmWanMbus0AValue24		OBJECT-TYPE
			SYNTAX	INTEGER
			MAX-ACCESS	read-only
			STATUS	current
			::= { hmWanMbus0A 79 }

hmWanMbus0AVIF25		OBJECT-TYPE
			SYNTAX	INTEGER
			MAX-ACCESS	read-only
			STATUS	current
			::= { hmWanMbus0A 80 }

hmWanMbus0AValue25		OBJECT-TYPE
			SYNTAX	INTEGER
			MAX-ACCESS	read-only
			STATUS	current
			::= { hmWanMbus0A 81 }

hmWanMbus0AVIF26		OBJECT-TYPE
			SYNTAX	INTEGER
			MAX-ACCESS	read-only
			STATUS	current
			::= { hmWanMbus0A 82 }

hmWanMbus0AValue26		OBJECT-TYPE
			SYNTAX	INTEGER
			MAX-ACCESS	read-only
			STATUS	current
			::= { hmWanMbus0A 83 }

hmWanMbus0AVIF27		OBJECT-TYPE
			SYNTAX	INTEGER
			MAX-ACCESS	read-only
			STATUS	current
			::= { hmWanMbus0A 84 }

hmWanMbus0AValue27		OBJECT-TYPE
			SYNTAX	INTEGER
			MAX-ACCESS	read-only
			STATUS	current
			::= { hmWanMbus0A 85 }

hmWanMbus0AVIF28		OBJECT-TYPE
			SYNTAX	INTEGER
			MAX-ACCESS	read-only
			STATUS	current
			::= { hmWanMbus0A 86 }

hmWanMbus0AValue28		OBJECT-TYPE
			SYNTAX	INTEGER
			MAX-ACCESS	read-only
			STATUS	current
			::= { hmWanMbus0A 87 }

hmWanMbus0AVIF29		OBJECT-TYPE
			SYNTAX	INTEGER
			MAX-ACCESS	read-only
			STATUS	current
			::= { hmWanMbus0A 88 }

hmWanMbus0AValue29		OBJECT-TYPE
			SYNTAX	INTEGER
			MAX-ACCESS	read-only
			STATUS	current
			::= { hmWanMbus0A 89 }

hmWanMbus0AVIF2A		OBJECT-TYPE
			SYNTAX	INTEGER
			MAX-ACCESS	read-only
			STATUS	current
			::= { hmWanMbus0A 90 }

hmWanMbus0AValue2A		OBJECT-TYPE
			SYNTAX	INTEGER
			MAX-ACCESS	read-only
			STATUS	current
			::= { hmWanMbus0A 91 }

hmWanMbus0AVIF2B		OBJECT-TYPE
			SYNTAX	INTEGER
			MAX-ACCESS	read-only
			STATUS	current
			::= { hmWanMbus0A 92 }

hmWanMbus0AValue2B		OBJECT-TYPE
			SYNTAX	INTEGER
			MAX-ACCESS	read-only
			STATUS	current
			::= { hmWanMbus0A 93 }

hmWanMbus0AVIF2C		OBJECT-TYPE
			SYNTAX	INTEGER
			MAX-ACCESS	read-only
			STATUS	current
			::= { hmWanMbus0A 94 }

hmWanMbus0AValue2C		OBJECT-TYPE
			SYNTAX	INTEGER
			MAX-ACCESS	read-only
			STATUS	current
			::= { hmWanMbus0A 95 }

hmWanMbus0AVIF2D		OBJECT-TYPE
			SYNTAX	INTEGER
			MAX-ACCESS	read-only
			STATUS	current
			::= { hmWanMbus0A 96 }

hmWanMbus0AValue2D		OBJECT-TYPE
			SYNTAX	INTEGER
			MAX-ACCESS	read-only
			STATUS	current
			::= { hmWanMbus0A 97 }

hmWanMbus0AVIF2E		OBJECT-TYPE
			SYNTAX	INTEGER
			MAX-ACCESS	read-only
			STATUS	current
			::= { hmWanMbus0A 98 }

hmWanMbus0AValue2E		OBJECT-TYPE
			SYNTAX	INTEGER
			MAX-ACCESS	read-only
			STATUS	current
			::= { hmWanMbus0A 99 }

hmWanMbus0AVIF2F		OBJECT-TYPE
			SYNTAX	INTEGER
			MAX-ACCESS	read-only
			STATUS	current
			::= { hmWanMbus0A 100 }

hmWanMbus0AValue2F		OBJECT-TYPE
			SYNTAX	INTEGER
			MAX-ACCESS	read-only
			STATUS	current
			::= { hmWanMbus0A 101 }

hmWanMbus0B			OBJECT IDENTIFIER ::= { hmWanMbus 11 }

hmWanMbus0BIdNumber		OBJECT-TYPE
			SYNTAX	Gauge32
			MAX-ACCESS	read-only
			STATUS	current
			::= { hmWanMbus0B 1 }

hmWanMbus0BManufacturer	OBJECT-TYPE
			SYNTAX	Gauge32
			MAX-ACCESS	read-only
			STATUS	current
			::= { hmWanMbus0B 2 }

hmWanMbus0BVersion		OBJECT-TYPE
			SYNTAX	Gauge32
			MAX-ACCESS	read-only
			STATUS	current
			::= { hmWanMbus0B 3 }

hmWanMbus0BMedium		OBJECT-TYPE
			SYNTAX	Gauge32
			MAX-ACCESS	read-only
			STATUS	current
			::= { hmWanMbus0B 4 }

hmWanMbus0BStatus		OBJECT-TYPE
			SYNTAX	Gauge32
			MAX-ACCESS	read-only
			STATUS	current
			::= { hmWanMbus0B 5 }

hmWanMbus0BVIF00		OBJECT-TYPE
			SYNTAX	INTEGER
			MAX-ACCESS	read-only
			STATUS	current
			::= { hmWanMbus0B 6 }

hmWanMbus0BValue00		OBJECT-TYPE
			SYNTAX	INTEGER
			MAX-ACCESS	read-only
			STATUS	current
			::= { hmWanMbus0B 7 }

hmWanMbus0BVIF01		OBJECT-TYPE
			SYNTAX	INTEGER
			MAX-ACCESS	read-only
			STATUS	current
			::= { hmWanMbus0B 8 }

hmWanMbus0BValue01		OBJECT-TYPE
			SYNTAX	INTEGER
			MAX-ACCESS	read-only
			STATUS	current
			::= { hmWanMbus0B 9 }

hmWanMbus0BVIF02		OBJECT-TYPE
			SYNTAX	INTEGER
			MAX-ACCESS	read-only
			STATUS	current
			::= { hmWanMbus0B 10 }

hmWanMbus0BValue02		OBJECT-TYPE
			SYNTAX	INTEGER
			MAX-ACCESS	read-only
			STATUS	current
			::= { hmWanMbus0B 11 }

hmWanMbus0BVIF03		OBJECT-TYPE
			SYNTAX	INTEGER
			MAX-ACCESS	read-only
			STATUS	current
			::= { hmWanMbus0B 12 }

hmWanMbus0BValue03		OBJECT-TYPE
			SYNTAX	INTEGER
			MAX-ACCESS	read-only
			STATUS	current
			::= { hmWanMbus0B 13 }

hmWanMbus0BVIF04		OBJECT-TYPE
			SYNTAX	INTEGER
			MAX-ACCESS	read-only
			STATUS	current
			::= { hmWanMbus0B 14 }

hmWanMbus0BValue04		OBJECT-TYPE
			SYNTAX	INTEGER
			MAX-ACCESS	read-only
			STATUS	current
			::= { hmWanMbus0B 15 }

hmWanMbus0BVIF05		OBJECT-TYPE
			SYNTAX	INTEGER
			MAX-ACCESS	read-only
			STATUS	current
			::= { hmWanMbus0B 16 }

hmWanMbus0BValue05		OBJECT-TYPE
			SYNTAX	INTEGER
			MAX-ACCESS	read-only
			STATUS	current
			::= { hmWanMbus0B 17 }

hmWanMbus0BVIF06		OBJECT-TYPE
			SYNTAX	INTEGER
			MAX-ACCESS	read-only
			STATUS	current
			::= { hmWanMbus0B 18 }

hmWanMbus0BValue06		OBJECT-TYPE
			SYNTAX	INTEGER
			MAX-ACCESS	read-only
			STATUS	current
			::= { hmWanMbus0B 19 }

hmWanMbus0BVIF07		OBJECT-TYPE
			SYNTAX	INTEGER
			MAX-ACCESS	read-only
			STATUS	current
			::= { hmWanMbus0B 20 }

hmWanMbus0BValue07		OBJECT-TYPE
			SYNTAX	INTEGER
			MAX-ACCESS	read-only
			STATUS	current
			::= { hmWanMbus0B 21 }

hmWanMbus0BVIF08		OBJECT-TYPE
			SYNTAX	INTEGER
			MAX-ACCESS	read-only
			STATUS	current
			::= { hmWanMbus0B 22 }

hmWanMbus0BValue08		OBJECT-TYPE
			SYNTAX	INTEGER
			MAX-ACCESS	read-only
			STATUS	current
			::= { hmWanMbus0B 23 }

hmWanMbus0BVIF09		OBJECT-TYPE
			SYNTAX	INTEGER
			MAX-ACCESS	read-only
			STATUS	current
			::= { hmWanMbus0B 24 }

hmWanMbus0BValue09		OBJECT-TYPE
			SYNTAX	INTEGER
			MAX-ACCESS	read-only
			STATUS	current
			::= { hmWanMbus0B 25 }

hmWanMbus0BVIF0A		OBJECT-TYPE
			SYNTAX	INTEGER
			MAX-ACCESS	read-only
			STATUS	current
			::= { hmWanMbus0B 26 }

hmWanMbus0BValue0A		OBJECT-TYPE
			SYNTAX	INTEGER
			MAX-ACCESS	read-only
			STATUS	current
			::= { hmWanMbus0B 27 }

hmWanMbus0BVIF0B		OBJECT-TYPE
			SYNTAX	INTEGER
			MAX-ACCESS	read-only
			STATUS	current
			::= { hmWanMbus0B 28 }

hmWanMbus0BValue0B		OBJECT-TYPE
			SYNTAX	INTEGER
			MAX-ACCESS	read-only
			STATUS	current
			::= { hmWanMbus0B 29 }

hmWanMbus0BVIF0C		OBJECT-TYPE
			SYNTAX	INTEGER
			MAX-ACCESS	read-only
			STATUS	current
			::= { hmWanMbus0B 30 }

hmWanMbus0BValue0C		OBJECT-TYPE
			SYNTAX	INTEGER
			MAX-ACCESS	read-only
			STATUS	current
			::= { hmWanMbus0B 31 }

hmWanMbus0BVIF0D		OBJECT-TYPE
			SYNTAX	INTEGER
			MAX-ACCESS	read-only
			STATUS	current
			::= { hmWanMbus0B 32 }

hmWanMbus0BValue0D		OBJECT-TYPE
			SYNTAX	INTEGER
			MAX-ACCESS	read-only
			STATUS	current
			::= { hmWanMbus0B 33 }

hmWanMbus0BVIF0E		OBJECT-TYPE
			SYNTAX	INTEGER
			MAX-ACCESS	read-only
			STATUS	current
			::= { hmWanMbus0B 34 }

hmWanMbus0BValue0E		OBJECT-TYPE
			SYNTAX	INTEGER
			MAX-ACCESS	read-only
			STATUS	current
			::= { hmWanMbus0B 35 }

hmWanMbus0BVIF0F		OBJECT-TYPE
			SYNTAX	INTEGER
			MAX-ACCESS	read-only
			STATUS	current
			::= { hmWanMbus0B 36 }

hmWanMbus0BValue0F		OBJECT-TYPE
			SYNTAX	INTEGER
			MAX-ACCESS	read-only
			STATUS	current
			::= { hmWanMbus0B 37 }

hmWanMbus0BVIF10		OBJECT-TYPE
			SYNTAX	INTEGER
			MAX-ACCESS	read-only
			STATUS	current
			::= { hmWanMbus0B 38 }

hmWanMbus0BValue10		OBJECT-TYPE
			SYNTAX	INTEGER
			MAX-ACCESS	read-only
			STATUS	current
			::= { hmWanMbus0B 39 }

hmWanMbus0BVIF11		OBJECT-TYPE
			SYNTAX	INTEGER
			MAX-ACCESS	read-only
			STATUS	current
			::= { hmWanMbus0B 40 }

hmWanMbus0BValue11		OBJECT-TYPE
			SYNTAX	INTEGER
			MAX-ACCESS	read-only
			STATUS	current
			::= { hmWanMbus0B 41 }

hmWanMbus0BVIF12		OBJECT-TYPE
			SYNTAX	INTEGER
			MAX-ACCESS	read-only
			STATUS	current
			::= { hmWanMbus0B 42 }

hmWanMbus0BValue12		OBJECT-TYPE
			SYNTAX	INTEGER
			MAX-ACCESS	read-only
			STATUS	current
			::= { hmWanMbus0B 43 }

hmWanMbus0BVIF13		OBJECT-TYPE
			SYNTAX	INTEGER
			MAX-ACCESS	read-only
			STATUS	current
			::= { hmWanMbus0B 44 }

hmWanMbus0BValue13		OBJECT-TYPE
			SYNTAX	INTEGER
			MAX-ACCESS	read-only
			STATUS	current
			::= { hmWanMbus0B 45 }

hmWanMbus0BVIF14		OBJECT-TYPE
			SYNTAX	INTEGER
			MAX-ACCESS	read-only
			STATUS	current
			::= { hmWanMbus0B 46 }

hmWanMbus0BValue14		OBJECT-TYPE
			SYNTAX	INTEGER
			MAX-ACCESS	read-only
			STATUS	current
			::= { hmWanMbus0B 47 }

hmWanMbus0BVIF15		OBJECT-TYPE
			SYNTAX	INTEGER
			MAX-ACCESS	read-only
			STATUS	current
			::= { hmWanMbus0B 48 }

hmWanMbus0BValue15		OBJECT-TYPE
			SYNTAX	INTEGER
			MAX-ACCESS	read-only
			STATUS	current
			::= { hmWanMbus0B 49 }

hmWanMbus0BVIF16		OBJECT-TYPE
			SYNTAX	INTEGER
			MAX-ACCESS	read-only
			STATUS	current
			::= { hmWanMbus0B 50 }

hmWanMbus0BValue16		OBJECT-TYPE
			SYNTAX	INTEGER
			MAX-ACCESS	read-only
			STATUS	current
			::= { hmWanMbus0B 51 }

hmWanMbus0BVIF17		OBJECT-TYPE
			SYNTAX	INTEGER
			MAX-ACCESS	read-only
			STATUS	current
			::= { hmWanMbus0B 52 }

hmWanMbus0BValue17		OBJECT-TYPE
			SYNTAX	INTEGER
			MAX-ACCESS	read-only
			STATUS	current
			::= { hmWanMbus0B 53 }

hmWanMbus0BVIF18		OBJECT-TYPE
			SYNTAX	INTEGER
			MAX-ACCESS	read-only
			STATUS	current
			::= { hmWanMbus0B 54 }

hmWanMbus0BValue18		OBJECT-TYPE
			SYNTAX	INTEGER
			MAX-ACCESS	read-only
			STATUS	current
			::= { hmWanMbus0B 55 }

hmWanMbus0BVIF19		OBJECT-TYPE
			SYNTAX	INTEGER
			MAX-ACCESS	read-only
			STATUS	current
			::= { hmWanMbus0B 56 }

hmWanMbus0BValue19		OBJECT-TYPE
			SYNTAX	INTEGER
			MAX-ACCESS	read-only
			STATUS	current
			::= { hmWanMbus0B 57 }

hmWanMbus0BVIF1A		OBJECT-TYPE
			SYNTAX	INTEGER
			MAX-ACCESS	read-only
			STATUS	current
			::= { hmWanMbus0B 58 }

hmWanMbus0BValue1A		OBJECT-TYPE
			SYNTAX	INTEGER
			MAX-ACCESS	read-only
			STATUS	current
			::= { hmWanMbus0B 59 }

hmWanMbus0BVIF1B		OBJECT-TYPE
			SYNTAX	INTEGER
			MAX-ACCESS	read-only
			STATUS	current
			::= { hmWanMbus0B 60 }

hmWanMbus0BValue1B		OBJECT-TYPE
			SYNTAX	INTEGER
			MAX-ACCESS	read-only
			STATUS	current
			::= { hmWanMbus0B 61 }

hmWanMbus0BVIF1C		OBJECT-TYPE
			SYNTAX	INTEGER
			MAX-ACCESS	read-only
			STATUS	current
			::= { hmWanMbus0B 62 }

hmWanMbus0BValue1C		OBJECT-TYPE
			SYNTAX	INTEGER
			MAX-ACCESS	read-only
			STATUS	current
			::= { hmWanMbus0B 63 }

hmWanMbus0BVIF1D		OBJECT-TYPE
			SYNTAX	INTEGER
			MAX-ACCESS	read-only
			STATUS	current
			::= { hmWanMbus0B 64 }

hmWanMbus0BValue1D		OBJECT-TYPE
			SYNTAX	INTEGER
			MAX-ACCESS	read-only
			STATUS	current
			::= { hmWanMbus0B 65 }

hmWanMbus0BVIF1E		OBJECT-TYPE
			SYNTAX	INTEGER
			MAX-ACCESS	read-only
			STATUS	current
			::= { hmWanMbus0B 66 }

hmWanMbus0BValue1E		OBJECT-TYPE
			SYNTAX	INTEGER
			MAX-ACCESS	read-only
			STATUS	current
			::= { hmWanMbus0B 67 }

hmWanMbus0BVIF1F		OBJECT-TYPE
			SYNTAX	INTEGER
			MAX-ACCESS	read-only
			STATUS	current
			::= { hmWanMbus0B 68 }

hmWanMbus0BValue1F		OBJECT-TYPE
			SYNTAX	INTEGER
			MAX-ACCESS	read-only
			STATUS	current
			::= { hmWanMbus0B 69 }

hmWanMbus0BVIF20		OBJECT-TYPE
			SYNTAX	INTEGER
			MAX-ACCESS	read-only
			STATUS	current
			::= { hmWanMbus0B 70 }

hmWanMbus0BValue20		OBJECT-TYPE
			SYNTAX	INTEGER
			MAX-ACCESS	read-only
			STATUS	current
			::= { hmWanMbus0B 71 }

hmWanMbus0BVIF21		OBJECT-TYPE
			SYNTAX	INTEGER
			MAX-ACCESS	read-only
			STATUS	current
			::= { hmWanMbus0B 72 }

hmWanMbus0BValue21		OBJECT-TYPE
			SYNTAX	INTEGER
			MAX-ACCESS	read-only
			STATUS	current
			::= { hmWanMbus0B 73 }

hmWanMbus0BVIF22		OBJECT-TYPE
			SYNTAX	INTEGER
			MAX-ACCESS	read-only
			STATUS	current
			::= { hmWanMbus0B 74 }

hmWanMbus0BValue22		OBJECT-TYPE
			SYNTAX	INTEGER
			MAX-ACCESS	read-only
			STATUS	current
			::= { hmWanMbus0B 75 }

hmWanMbus0BVIF23		OBJECT-TYPE
			SYNTAX	INTEGER
			MAX-ACCESS	read-only
			STATUS	current
			::= { hmWanMbus0B 76 }

hmWanMbus0BValue23		OBJECT-TYPE
			SYNTAX	INTEGER
			MAX-ACCESS	read-only
			STATUS	current
			::= { hmWanMbus0B 77 }

hmWanMbus0BVIF24		OBJECT-TYPE
			SYNTAX	INTEGER
			MAX-ACCESS	read-only
			STATUS	current
			::= { hmWanMbus0B 78 }

hmWanMbus0BValue24		OBJECT-TYPE
			SYNTAX	INTEGER
			MAX-ACCESS	read-only
			STATUS	current
			::= { hmWanMbus0B 79 }

hmWanMbus0BVIF25		OBJECT-TYPE
			SYNTAX	INTEGER
			MAX-ACCESS	read-only
			STATUS	current
			::= { hmWanMbus0B 80 }

hmWanMbus0BValue25		OBJECT-TYPE
			SYNTAX	INTEGER
			MAX-ACCESS	read-only
			STATUS	current
			::= { hmWanMbus0B 81 }

hmWanMbus0BVIF26		OBJECT-TYPE
			SYNTAX	INTEGER
			MAX-ACCESS	read-only
			STATUS	current
			::= { hmWanMbus0B 82 }

hmWanMbus0BValue26		OBJECT-TYPE
			SYNTAX	INTEGER
			MAX-ACCESS	read-only
			STATUS	current
			::= { hmWanMbus0B 83 }

hmWanMbus0BVIF27		OBJECT-TYPE
			SYNTAX	INTEGER
			MAX-ACCESS	read-only
			STATUS	current
			::= { hmWanMbus0B 84 }

hmWanMbus0BValue27		OBJECT-TYPE
			SYNTAX	INTEGER
			MAX-ACCESS	read-only
			STATUS	current
			::= { hmWanMbus0B 85 }

hmWanMbus0BVIF28		OBJECT-TYPE
			SYNTAX	INTEGER
			MAX-ACCESS	read-only
			STATUS	current
			::= { hmWanMbus0B 86 }

hmWanMbus0BValue28		OBJECT-TYPE
			SYNTAX	INTEGER
			MAX-ACCESS	read-only
			STATUS	current
			::= { hmWanMbus0B 87 }

hmWanMbus0BVIF29		OBJECT-TYPE
			SYNTAX	INTEGER
			MAX-ACCESS	read-only
			STATUS	current
			::= { hmWanMbus0B 88 }

hmWanMbus0BValue29		OBJECT-TYPE
			SYNTAX	INTEGER
			MAX-ACCESS	read-only
			STATUS	current
			::= { hmWanMbus0B 89 }

hmWanMbus0BVIF2A		OBJECT-TYPE
			SYNTAX	INTEGER
			MAX-ACCESS	read-only
			STATUS	current
			::= { hmWanMbus0B 90 }

hmWanMbus0BValue2A		OBJECT-TYPE
			SYNTAX	INTEGER
			MAX-ACCESS	read-only
			STATUS	current
			::= { hmWanMbus0B 91 }

hmWanMbus0BVIF2B		OBJECT-TYPE
			SYNTAX	INTEGER
			MAX-ACCESS	read-only
			STATUS	current
			::= { hmWanMbus0B 92 }

hmWanMbus0BValue2B		OBJECT-TYPE
			SYNTAX	INTEGER
			MAX-ACCESS	read-only
			STATUS	current
			::= { hmWanMbus0B 93 }

hmWanMbus0BVIF2C		OBJECT-TYPE
			SYNTAX	INTEGER
			MAX-ACCESS	read-only
			STATUS	current
			::= { hmWanMbus0B 94 }

hmWanMbus0BValue2C		OBJECT-TYPE
			SYNTAX	INTEGER
			MAX-ACCESS	read-only
			STATUS	current
			::= { hmWanMbus0B 95 }

hmWanMbus0BVIF2D		OBJECT-TYPE
			SYNTAX	INTEGER
			MAX-ACCESS	read-only
			STATUS	current
			::= { hmWanMbus0B 96 }

hmWanMbus0BValue2D		OBJECT-TYPE
			SYNTAX	INTEGER
			MAX-ACCESS	read-only
			STATUS	current
			::= { hmWanMbus0B 97 }

hmWanMbus0BVIF2E		OBJECT-TYPE
			SYNTAX	INTEGER
			MAX-ACCESS	read-only
			STATUS	current
			::= { hmWanMbus0B 98 }

hmWanMbus0BValue2E		OBJECT-TYPE
			SYNTAX	INTEGER
			MAX-ACCESS	read-only
			STATUS	current
			::= { hmWanMbus0B 99 }

hmWanMbus0BVIF2F		OBJECT-TYPE
			SYNTAX	INTEGER
			MAX-ACCESS	read-only
			STATUS	current
			::= { hmWanMbus0B 100 }

hmWanMbus0BValue2F		OBJECT-TYPE
			SYNTAX	INTEGER
			MAX-ACCESS	read-only
			STATUS	current
			::= { hmWanMbus0B 101 }

hmWanMbus0C			OBJECT IDENTIFIER ::= { hmWanMbus 12 }

hmWanMbus0CIdNumber		OBJECT-TYPE
			SYNTAX	Gauge32
			MAX-ACCESS	read-only
			STATUS	current
			::= { hmWanMbus0C 1 }

hmWanMbus0CManufacturer	OBJECT-TYPE
			SYNTAX	Gauge32
			MAX-ACCESS	read-only
			STATUS	current
			::= { hmWanMbus0C 2 }

hmWanMbus0CVersion		OBJECT-TYPE
			SYNTAX	Gauge32
			MAX-ACCESS	read-only
			STATUS	current
			::= { hmWanMbus0C 3 }

hmWanMbus0CMedium		OBJECT-TYPE
			SYNTAX	Gauge32
			MAX-ACCESS	read-only
			STATUS	current
			::= { hmWanMbus0C 4 }

hmWanMbus0CStatus		OBJECT-TYPE
			SYNTAX	Gauge32
			MAX-ACCESS	read-only
			STATUS	current
			::= { hmWanMbus0C 5 }

hmWanMbus0CVIF00		OBJECT-TYPE
			SYNTAX	INTEGER
			MAX-ACCESS	read-only
			STATUS	current
			::= { hmWanMbus0C 6 }

hmWanMbus0CValue00		OBJECT-TYPE
			SYNTAX	INTEGER
			MAX-ACCESS	read-only
			STATUS	current
			::= { hmWanMbus0C 7 }

hmWanMbus0CVIF01		OBJECT-TYPE
			SYNTAX	INTEGER
			MAX-ACCESS	read-only
			STATUS	current
			::= { hmWanMbus0C 8 }

hmWanMbus0CValue01		OBJECT-TYPE
			SYNTAX	INTEGER
			MAX-ACCESS	read-only
			STATUS	current
			::= { hmWanMbus0C 9 }

hmWanMbus0CVIF02		OBJECT-TYPE
			SYNTAX	INTEGER
			MAX-ACCESS	read-only
			STATUS	current
			::= { hmWanMbus0C 10 }

hmWanMbus0CValue02		OBJECT-TYPE
			SYNTAX	INTEGER
			MAX-ACCESS	read-only
			STATUS	current
			::= { hmWanMbus0C 11 }

hmWanMbus0CVIF03		OBJECT-TYPE
			SYNTAX	INTEGER
			MAX-ACCESS	read-only
			STATUS	current
			::= { hmWanMbus0C 12 }

hmWanMbus0CValue03		OBJECT-TYPE
			SYNTAX	INTEGER
			MAX-ACCESS	read-only
			STATUS	current
			::= { hmWanMbus0C 13 }

hmWanMbus0CVIF04		OBJECT-TYPE
			SYNTAX	INTEGER
			MAX-ACCESS	read-only
			STATUS	current
			::= { hmWanMbus0C 14 }

hmWanMbus0CValue04		OBJECT-TYPE
			SYNTAX	INTEGER
			MAX-ACCESS	read-only
			STATUS	current
			::= { hmWanMbus0C 15 }

hmWanMbus0CVIF05		OBJECT-TYPE
			SYNTAX	INTEGER
			MAX-ACCESS	read-only
			STATUS	current
			::= { hmWanMbus0C 16 }

hmWanMbus0CValue05		OBJECT-TYPE
			SYNTAX	INTEGER
			MAX-ACCESS	read-only
			STATUS	current
			::= { hmWanMbus0C 17 }

hmWanMbus0CVIF06		OBJECT-TYPE
			SYNTAX	INTEGER
			MAX-ACCESS	read-only
			STATUS	current
			::= { hmWanMbus0C 18 }

hmWanMbus0CValue06		OBJECT-TYPE
			SYNTAX	INTEGER
			MAX-ACCESS	read-only
			STATUS	current
			::= { hmWanMbus0C 19 }

hmWanMbus0CVIF07		OBJECT-TYPE
			SYNTAX	INTEGER
			MAX-ACCESS	read-only
			STATUS	current
			::= { hmWanMbus0C 20 }

hmWanMbus0CValue07		OBJECT-TYPE
			SYNTAX	INTEGER
			MAX-ACCESS	read-only
			STATUS	current
			::= { hmWanMbus0C 21 }

hmWanMbus0CVIF08		OBJECT-TYPE
			SYNTAX	INTEGER
			MAX-ACCESS	read-only
			STATUS	current
			::= { hmWanMbus0C 22 }

hmWanMbus0CValue08		OBJECT-TYPE
			SYNTAX	INTEGER
			MAX-ACCESS	read-only
			STATUS	current
			::= { hmWanMbus0C 23 }

hmWanMbus0CVIF09		OBJECT-TYPE
			SYNTAX	INTEGER
			MAX-ACCESS	read-only
			STATUS	current
			::= { hmWanMbus0C 24 }

hmWanMbus0CValue09		OBJECT-TYPE
			SYNTAX	INTEGER
			MAX-ACCESS	read-only
			STATUS	current
			::= { hmWanMbus0C 25 }

hmWanMbus0CVIF0A		OBJECT-TYPE
			SYNTAX	INTEGER
			MAX-ACCESS	read-only
			STATUS	current
			::= { hmWanMbus0C 26 }

hmWanMbus0CValue0A		OBJECT-TYPE
			SYNTAX	INTEGER
			MAX-ACCESS	read-only
			STATUS	current
			::= { hmWanMbus0C 27 }

hmWanMbus0CVIF0B		OBJECT-TYPE
			SYNTAX	INTEGER
			MAX-ACCESS	read-only
			STATUS	current
			::= { hmWanMbus0C 28 }

hmWanMbus0CValue0B		OBJECT-TYPE
			SYNTAX	INTEGER
			MAX-ACCESS	read-only
			STATUS	current
			::= { hmWanMbus0C 29 }

hmWanMbus0CVIF0C		OBJECT-TYPE
			SYNTAX	INTEGER
			MAX-ACCESS	read-only
			STATUS	current
			::= { hmWanMbus0C 30 }

hmWanMbus0CValue0C		OBJECT-TYPE
			SYNTAX	INTEGER
			MAX-ACCESS	read-only
			STATUS	current
			::= { hmWanMbus0C 31 }

hmWanMbus0CVIF0D		OBJECT-TYPE
			SYNTAX	INTEGER
			MAX-ACCESS	read-only
			STATUS	current
			::= { hmWanMbus0C 32 }

hmWanMbus0CValue0D		OBJECT-TYPE
			SYNTAX	INTEGER
			MAX-ACCESS	read-only
			STATUS	current
			::= { hmWanMbus0C 33 }

hmWanMbus0CVIF0E		OBJECT-TYPE
			SYNTAX	INTEGER
			MAX-ACCESS	read-only
			STATUS	current
			::= { hmWanMbus0C 34 }

hmWanMbus0CValue0E		OBJECT-TYPE
			SYNTAX	INTEGER
			MAX-ACCESS	read-only
			STATUS	current
			::= { hmWanMbus0C 35 }

hmWanMbus0CVIF0F		OBJECT-TYPE
			SYNTAX	INTEGER
			MAX-ACCESS	read-only
			STATUS	current
			::= { hmWanMbus0C 36 }

hmWanMbus0CValue0F		OBJECT-TYPE
			SYNTAX	INTEGER
			MAX-ACCESS	read-only
			STATUS	current
			::= { hmWanMbus0C 37 }

hmWanMbus0CVIF10		OBJECT-TYPE
			SYNTAX	INTEGER
			MAX-ACCESS	read-only
			STATUS	current
			::= { hmWanMbus0C 38 }

hmWanMbus0CValue10		OBJECT-TYPE
			SYNTAX	INTEGER
			MAX-ACCESS	read-only
			STATUS	current
			::= { hmWanMbus0C 39 }

hmWanMbus0CVIF11		OBJECT-TYPE
			SYNTAX	INTEGER
			MAX-ACCESS	read-only
			STATUS	current
			::= { hmWanMbus0C 40 }

hmWanMbus0CValue11		OBJECT-TYPE
			SYNTAX	INTEGER
			MAX-ACCESS	read-only
			STATUS	current
			::= { hmWanMbus0C 41 }

hmWanMbus0CVIF12		OBJECT-TYPE
			SYNTAX	INTEGER
			MAX-ACCESS	read-only
			STATUS	current
			::= { hmWanMbus0C 42 }

hmWanMbus0CValue12		OBJECT-TYPE
			SYNTAX	INTEGER
			MAX-ACCESS	read-only
			STATUS	current
			::= { hmWanMbus0C 43 }

hmWanMbus0CVIF13		OBJECT-TYPE
			SYNTAX	INTEGER
			MAX-ACCESS	read-only
			STATUS	current
			::= { hmWanMbus0C 44 }

hmWanMbus0CValue13		OBJECT-TYPE
			SYNTAX	INTEGER
			MAX-ACCESS	read-only
			STATUS	current
			::= { hmWanMbus0C 45 }

hmWanMbus0CVIF14		OBJECT-TYPE
			SYNTAX	INTEGER
			MAX-ACCESS	read-only
			STATUS	current
			::= { hmWanMbus0C 46 }

hmWanMbus0CValue14		OBJECT-TYPE
			SYNTAX	INTEGER
			MAX-ACCESS	read-only
			STATUS	current
			::= { hmWanMbus0C 47 }

hmWanMbus0CVIF15		OBJECT-TYPE
			SYNTAX	INTEGER
			MAX-ACCESS	read-only
			STATUS	current
			::= { hmWanMbus0C 48 }

hmWanMbus0CValue15		OBJECT-TYPE
			SYNTAX	INTEGER
			MAX-ACCESS	read-only
			STATUS	current
			::= { hmWanMbus0C 49 }

hmWanMbus0CVIF16		OBJECT-TYPE
			SYNTAX	INTEGER
			MAX-ACCESS	read-only
			STATUS	current
			::= { hmWanMbus0C 50 }

hmWanMbus0CValue16		OBJECT-TYPE
			SYNTAX	INTEGER
			MAX-ACCESS	read-only
			STATUS	current
			::= { hmWanMbus0C 51 }

hmWanMbus0CVIF17		OBJECT-TYPE
			SYNTAX	INTEGER
			MAX-ACCESS	read-only
			STATUS	current
			::= { hmWanMbus0C 52 }

hmWanMbus0CValue17		OBJECT-TYPE
			SYNTAX	INTEGER
			MAX-ACCESS	read-only
			STATUS	current
			::= { hmWanMbus0C 53 }

hmWanMbus0CVIF18		OBJECT-TYPE
			SYNTAX	INTEGER
			MAX-ACCESS	read-only
			STATUS	current
			::= { hmWanMbus0C 54 }

hmWanMbus0CValue18		OBJECT-TYPE
			SYNTAX	INTEGER
			MAX-ACCESS	read-only
			STATUS	current
			::= { hmWanMbus0C 55 }

hmWanMbus0CVIF19		OBJECT-TYPE
			SYNTAX	INTEGER
			MAX-ACCESS	read-only
			STATUS	current
			::= { hmWanMbus0C 56 }

hmWanMbus0CValue19		OBJECT-TYPE
			SYNTAX	INTEGER
			MAX-ACCESS	read-only
			STATUS	current
			::= { hmWanMbus0C 57 }

hmWanMbus0CVIF1A		OBJECT-TYPE
			SYNTAX	INTEGER
			MAX-ACCESS	read-only
			STATUS	current
			::= { hmWanMbus0C 58 }

hmWanMbus0CValue1A		OBJECT-TYPE
			SYNTAX	INTEGER
			MAX-ACCESS	read-only
			STATUS	current
			::= { hmWanMbus0C 59 }

hmWanMbus0CVIF1B		OBJECT-TYPE
			SYNTAX	INTEGER
			MAX-ACCESS	read-only
			STATUS	current
			::= { hmWanMbus0C 60 }

hmWanMbus0CValue1B		OBJECT-TYPE
			SYNTAX	INTEGER
			MAX-ACCESS	read-only
			STATUS	current
			::= { hmWanMbus0C 61 }

hmWanMbus0CVIF1C		OBJECT-TYPE
			SYNTAX	INTEGER
			MAX-ACCESS	read-only
			STATUS	current
			::= { hmWanMbus0C 62 }

hmWanMbus0CValue1C		OBJECT-TYPE
			SYNTAX	INTEGER
			MAX-ACCESS	read-only
			STATUS	current
			::= { hmWanMbus0C 63 }

hmWanMbus0CVIF1D		OBJECT-TYPE
			SYNTAX	INTEGER
			MAX-ACCESS	read-only
			STATUS	current
			::= { hmWanMbus0C 64 }

hmWanMbus0CValue1D		OBJECT-TYPE
			SYNTAX	INTEGER
			MAX-ACCESS	read-only
			STATUS	current
			::= { hmWanMbus0C 65 }

hmWanMbus0CVIF1E		OBJECT-TYPE
			SYNTAX	INTEGER
			MAX-ACCESS	read-only
			STATUS	current
			::= { hmWanMbus0C 66 }

hmWanMbus0CValue1E		OBJECT-TYPE
			SYNTAX	INTEGER
			MAX-ACCESS	read-only
			STATUS	current
			::= { hmWanMbus0C 67 }

hmWanMbus0CVIF1F		OBJECT-TYPE
			SYNTAX	INTEGER
			MAX-ACCESS	read-only
			STATUS	current
			::= { hmWanMbus0C 68 }

hmWanMbus0CValue1F		OBJECT-TYPE
			SYNTAX	INTEGER
			MAX-ACCESS	read-only
			STATUS	current
			::= { hmWanMbus0C 69 }

hmWanMbus0CVIF20		OBJECT-TYPE
			SYNTAX	INTEGER
			MAX-ACCESS	read-only
			STATUS	current
			::= { hmWanMbus0C 70 }

hmWanMbus0CValue20		OBJECT-TYPE
			SYNTAX	INTEGER
			MAX-ACCESS	read-only
			STATUS	current
			::= { hmWanMbus0C 71 }

hmWanMbus0CVIF21		OBJECT-TYPE
			SYNTAX	INTEGER
			MAX-ACCESS	read-only
			STATUS	current
			::= { hmWanMbus0C 72 }

hmWanMbus0CValue21		OBJECT-TYPE
			SYNTAX	INTEGER
			MAX-ACCESS	read-only
			STATUS	current
			::= { hmWanMbus0C 73 }

hmWanMbus0CVIF22		OBJECT-TYPE
			SYNTAX	INTEGER
			MAX-ACCESS	read-only
			STATUS	current
			::= { hmWanMbus0C 74 }

hmWanMbus0CValue22		OBJECT-TYPE
			SYNTAX	INTEGER
			MAX-ACCESS	read-only
			STATUS	current
			::= { hmWanMbus0C 75 }

hmWanMbus0CVIF23		OBJECT-TYPE
			SYNTAX	INTEGER
			MAX-ACCESS	read-only
			STATUS	current
			::= { hmWanMbus0C 76 }

hmWanMbus0CValue23		OBJECT-TYPE
			SYNTAX	INTEGER
			MAX-ACCESS	read-only
			STATUS	current
			::= { hmWanMbus0C 77 }

hmWanMbus0CVIF24		OBJECT-TYPE
			SYNTAX	INTEGER
			MAX-ACCESS	read-only
			STATUS	current
			::= { hmWanMbus0C 78 }

hmWanMbus0CValue24		OBJECT-TYPE
			SYNTAX	INTEGER
			MAX-ACCESS	read-only
			STATUS	current
			::= { hmWanMbus0C 79 }

hmWanMbus0CVIF25		OBJECT-TYPE
			SYNTAX	INTEGER
			MAX-ACCESS	read-only
			STATUS	current
			::= { hmWanMbus0C 80 }

hmWanMbus0CValue25		OBJECT-TYPE
			SYNTAX	INTEGER
			MAX-ACCESS	read-only
			STATUS	current
			::= { hmWanMbus0C 81 }

hmWanMbus0CVIF26		OBJECT-TYPE
			SYNTAX	INTEGER
			MAX-ACCESS	read-only
			STATUS	current
			::= { hmWanMbus0C 82 }

hmWanMbus0CValue26		OBJECT-TYPE
			SYNTAX	INTEGER
			MAX-ACCESS	read-only
			STATUS	current
			::= { hmWanMbus0C 83 }

hmWanMbus0CVIF27		OBJECT-TYPE
			SYNTAX	INTEGER
			MAX-ACCESS	read-only
			STATUS	current
			::= { hmWanMbus0C 84 }

hmWanMbus0CValue27		OBJECT-TYPE
			SYNTAX	INTEGER
			MAX-ACCESS	read-only
			STATUS	current
			::= { hmWanMbus0C 85 }

hmWanMbus0CVIF28		OBJECT-TYPE
			SYNTAX	INTEGER
			MAX-ACCESS	read-only
			STATUS	current
			::= { hmWanMbus0C 86 }

hmWanMbus0CValue28		OBJECT-TYPE
			SYNTAX	INTEGER
			MAX-ACCESS	read-only
			STATUS	current
			::= { hmWanMbus0C 87 }

hmWanMbus0CVIF29		OBJECT-TYPE
			SYNTAX	INTEGER
			MAX-ACCESS	read-only
			STATUS	current
			::= { hmWanMbus0C 88 }

hmWanMbus0CValue29		OBJECT-TYPE
			SYNTAX	INTEGER
			MAX-ACCESS	read-only
			STATUS	current
			::= { hmWanMbus0C 89 }

hmWanMbus0CVIF2A		OBJECT-TYPE
			SYNTAX	INTEGER
			MAX-ACCESS	read-only
			STATUS	current
			::= { hmWanMbus0C 90 }

hmWanMbus0CValue2A		OBJECT-TYPE
			SYNTAX	INTEGER
			MAX-ACCESS	read-only
			STATUS	current
			::= { hmWanMbus0C 91 }

hmWanMbus0CVIF2B		OBJECT-TYPE
			SYNTAX	INTEGER
			MAX-ACCESS	read-only
			STATUS	current
			::= { hmWanMbus0C 92 }

hmWanMbus0CValue2B		OBJECT-TYPE
			SYNTAX	INTEGER
			MAX-ACCESS	read-only
			STATUS	current
			::= { hmWanMbus0C 93 }

hmWanMbus0CVIF2C		OBJECT-TYPE
			SYNTAX	INTEGER
			MAX-ACCESS	read-only
			STATUS	current
			::= { hmWanMbus0C 94 }

hmWanMbus0CValue2C		OBJECT-TYPE
			SYNTAX	INTEGER
			MAX-ACCESS	read-only
			STATUS	current
			::= { hmWanMbus0C 95 }

hmWanMbus0CVIF2D		OBJECT-TYPE
			SYNTAX	INTEGER
			MAX-ACCESS	read-only
			STATUS	current
			::= { hmWanMbus0C 96 }

hmWanMbus0CValue2D		OBJECT-TYPE
			SYNTAX	INTEGER
			MAX-ACCESS	read-only
			STATUS	current
			::= { hmWanMbus0C 97 }

hmWanMbus0CVIF2E		OBJECT-TYPE
			SYNTAX	INTEGER
			MAX-ACCESS	read-only
			STATUS	current
			::= { hmWanMbus0C 98 }

hmWanMbus0CValue2E		OBJECT-TYPE
			SYNTAX	INTEGER
			MAX-ACCESS	read-only
			STATUS	current
			::= { hmWanMbus0C 99 }

hmWanMbus0CVIF2F		OBJECT-TYPE
			SYNTAX	INTEGER
			MAX-ACCESS	read-only
			STATUS	current
			::= { hmWanMbus0C 100 }

hmWanMbus0CValue2F		OBJECT-TYPE
			SYNTAX	INTEGER
			MAX-ACCESS	read-only
			STATUS	current
			::= { hmWanMbus0C 101 }

hmWanMbus0D			OBJECT IDENTIFIER ::= { hmWanMbus 13 }

hmWanMbus0DIdNumber		OBJECT-TYPE
			SYNTAX	Gauge32
			MAX-ACCESS	read-only
			STATUS	current
			::= { hmWanMbus0D 1 }

hmWanMbus0DManufacturer	OBJECT-TYPE
			SYNTAX	Gauge32
			MAX-ACCESS	read-only
			STATUS	current
			::= { hmWanMbus0D 2 }

hmWanMbus0DVersion		OBJECT-TYPE
			SYNTAX	Gauge32
			MAX-ACCESS	read-only
			STATUS	current
			::= { hmWanMbus0D 3 }

hmWanMbus0DMedium		OBJECT-TYPE
			SYNTAX	Gauge32
			MAX-ACCESS	read-only
			STATUS	current
			::= { hmWanMbus0D 4 }

hmWanMbus0DStatus		OBJECT-TYPE
			SYNTAX	Gauge32
			MAX-ACCESS	read-only
			STATUS	current
			::= { hmWanMbus0D 5 }

hmWanMbus0DVIF00		OBJECT-TYPE
			SYNTAX	INTEGER
			MAX-ACCESS	read-only
			STATUS	current
			::= { hmWanMbus0D 6 }

hmWanMbus0DValue00		OBJECT-TYPE
			SYNTAX	INTEGER
			MAX-ACCESS	read-only
			STATUS	current
			::= { hmWanMbus0D 7 }

hmWanMbus0DVIF01		OBJECT-TYPE
			SYNTAX	INTEGER
			MAX-ACCESS	read-only
			STATUS	current
			::= { hmWanMbus0D 8 }

hmWanMbus0DValue01		OBJECT-TYPE
			SYNTAX	INTEGER
			MAX-ACCESS	read-only
			STATUS	current
			::= { hmWanMbus0D 9 }

hmWanMbus0DVIF02		OBJECT-TYPE
			SYNTAX	INTEGER
			MAX-ACCESS	read-only
			STATUS	current
			::= { hmWanMbus0D 10 }

hmWanMbus0DValue02		OBJECT-TYPE
			SYNTAX	INTEGER
			MAX-ACCESS	read-only
			STATUS	current
			::= { hmWanMbus0D 11 }

hmWanMbus0DVIF03		OBJECT-TYPE
			SYNTAX	INTEGER
			MAX-ACCESS	read-only
			STATUS	current
			::= { hmWanMbus0D 12 }

hmWanMbus0DValue03		OBJECT-TYPE
			SYNTAX	INTEGER
			MAX-ACCESS	read-only
			STATUS	current
			::= { hmWanMbus0D 13 }

hmWanMbus0DVIF04		OBJECT-TYPE
			SYNTAX	INTEGER
			MAX-ACCESS	read-only
			STATUS	current
			::= { hmWanMbus0D 14 }

hmWanMbus0DValue04		OBJECT-TYPE
			SYNTAX	INTEGER
			MAX-ACCESS	read-only
			STATUS	current
			::= { hmWanMbus0D 15 }

hmWanMbus0DVIF05		OBJECT-TYPE
			SYNTAX	INTEGER
			MAX-ACCESS	read-only
			STATUS	current
			::= { hmWanMbus0D 16 }

hmWanMbus0DValue05		OBJECT-TYPE
			SYNTAX	INTEGER
			MAX-ACCESS	read-only
			STATUS	current
			::= { hmWanMbus0D 17 }

hmWanMbus0DVIF06		OBJECT-TYPE
			SYNTAX	INTEGER
			MAX-ACCESS	read-only
			STATUS	current
			::= { hmWanMbus0D 18 }

hmWanMbus0DValue06		OBJECT-TYPE
			SYNTAX	INTEGER
			MAX-ACCESS	read-only
			STATUS	current
			::= { hmWanMbus0D 19 }

hmWanMbus0DVIF07		OBJECT-TYPE
			SYNTAX	INTEGER
			MAX-ACCESS	read-only
			STATUS	current
			::= { hmWanMbus0D 20 }

hmWanMbus0DValue07		OBJECT-TYPE
			SYNTAX	INTEGER
			MAX-ACCESS	read-only
			STATUS	current
			::= { hmWanMbus0D 21 }

hmWanMbus0DVIF08		OBJECT-TYPE
			SYNTAX	INTEGER
			MAX-ACCESS	read-only
			STATUS	current
			::= { hmWanMbus0D 22 }

hmWanMbus0DValue08		OBJECT-TYPE
			SYNTAX	INTEGER
			MAX-ACCESS	read-only
			STATUS	current
			::= { hmWanMbus0D 23 }

hmWanMbus0DVIF09		OBJECT-TYPE
			SYNTAX	INTEGER
			MAX-ACCESS	read-only
			STATUS	current
			::= { hmWanMbus0D 24 }

hmWanMbus0DValue09		OBJECT-TYPE
			SYNTAX	INTEGER
			MAX-ACCESS	read-only
			STATUS	current
			::= { hmWanMbus0D 25 }

hmWanMbus0DVIF0A		OBJECT-TYPE
			SYNTAX	INTEGER
			MAX-ACCESS	read-only
			STATUS	current
			::= { hmWanMbus0D 26 }

hmWanMbus0DValue0A		OBJECT-TYPE
			SYNTAX	INTEGER
			MAX-ACCESS	read-only
			STATUS	current
			::= { hmWanMbus0D 27 }

hmWanMbus0DVIF0B		OBJECT-TYPE
			SYNTAX	INTEGER
			MAX-ACCESS	read-only
			STATUS	current
			::= { hmWanMbus0D 28 }

hmWanMbus0DValue0B		OBJECT-TYPE
			SYNTAX	INTEGER
			MAX-ACCESS	read-only
			STATUS	current
			::= { hmWanMbus0D 29 }

hmWanMbus0DVIF0C		OBJECT-TYPE
			SYNTAX	INTEGER
			MAX-ACCESS	read-only
			STATUS	current
			::= { hmWanMbus0D 30 }

hmWanMbus0DValue0C		OBJECT-TYPE
			SYNTAX	INTEGER
			MAX-ACCESS	read-only
			STATUS	current
			::= { hmWanMbus0D 31 }

hmWanMbus0DVIF0D		OBJECT-TYPE
			SYNTAX	INTEGER
			MAX-ACCESS	read-only
			STATUS	current
			::= { hmWanMbus0D 32 }

hmWanMbus0DValue0D		OBJECT-TYPE
			SYNTAX	INTEGER
			MAX-ACCESS	read-only
			STATUS	current
			::= { hmWanMbus0D 33 }

hmWanMbus0DVIF0E		OBJECT-TYPE
			SYNTAX	INTEGER
			MAX-ACCESS	read-only
			STATUS	current
			::= { hmWanMbus0D 34 }

hmWanMbus0DValue0E		OBJECT-TYPE
			SYNTAX	INTEGER
			MAX-ACCESS	read-only
			STATUS	current
			::= { hmWanMbus0D 35 }

hmWanMbus0DVIF0F		OBJECT-TYPE
			SYNTAX	INTEGER
			MAX-ACCESS	read-only
			STATUS	current
			::= { hmWanMbus0D 36 }

hmWanMbus0DValue0F		OBJECT-TYPE
			SYNTAX	INTEGER
			MAX-ACCESS	read-only
			STATUS	current
			::= { hmWanMbus0D 37 }

hmWanMbus0DVIF10		OBJECT-TYPE
			SYNTAX	INTEGER
			MAX-ACCESS	read-only
			STATUS	current
			::= { hmWanMbus0D 38 }

hmWanMbus0DValue10		OBJECT-TYPE
			SYNTAX	INTEGER
			MAX-ACCESS	read-only
			STATUS	current
			::= { hmWanMbus0D 39 }

hmWanMbus0DVIF11		OBJECT-TYPE
			SYNTAX	INTEGER
			MAX-ACCESS	read-only
			STATUS	current
			::= { hmWanMbus0D 40 }

hmWanMbus0DValue11		OBJECT-TYPE
			SYNTAX	INTEGER
			MAX-ACCESS	read-only
			STATUS	current
			::= { hmWanMbus0D 41 }

hmWanMbus0DVIF12		OBJECT-TYPE
			SYNTAX	INTEGER
			MAX-ACCESS	read-only
			STATUS	current
			::= { hmWanMbus0D 42 }

hmWanMbus0DValue12		OBJECT-TYPE
			SYNTAX	INTEGER
			MAX-ACCESS	read-only
			STATUS	current
			::= { hmWanMbus0D 43 }

hmWanMbus0DVIF13		OBJECT-TYPE
			SYNTAX	INTEGER
			MAX-ACCESS	read-only
			STATUS	current
			::= { hmWanMbus0D 44 }

hmWanMbus0DValue13		OBJECT-TYPE
			SYNTAX	INTEGER
			MAX-ACCESS	read-only
			STATUS	current
			::= { hmWanMbus0D 45 }

hmWanMbus0DVIF14		OBJECT-TYPE
			SYNTAX	INTEGER
			MAX-ACCESS	read-only
			STATUS	current
			::= { hmWanMbus0D 46 }

hmWanMbus0DValue14		OBJECT-TYPE
			SYNTAX	INTEGER
			MAX-ACCESS	read-only
			STATUS	current
			::= { hmWanMbus0D 47 }

hmWanMbus0DVIF15		OBJECT-TYPE
			SYNTAX	INTEGER
			MAX-ACCESS	read-only
			STATUS	current
			::= { hmWanMbus0D 48 }

hmWanMbus0DValue15		OBJECT-TYPE
			SYNTAX	INTEGER
			MAX-ACCESS	read-only
			STATUS	current
			::= { hmWanMbus0D 49 }

hmWanMbus0DVIF16		OBJECT-TYPE
			SYNTAX	INTEGER
			MAX-ACCESS	read-only
			STATUS	current
			::= { hmWanMbus0D 50 }

hmWanMbus0DValue16		OBJECT-TYPE
			SYNTAX	INTEGER
			MAX-ACCESS	read-only
			STATUS	current
			::= { hmWanMbus0D 51 }

hmWanMbus0DVIF17		OBJECT-TYPE
			SYNTAX	INTEGER
			MAX-ACCESS	read-only
			STATUS	current
			::= { hmWanMbus0D 52 }

hmWanMbus0DValue17		OBJECT-TYPE
			SYNTAX	INTEGER
			MAX-ACCESS	read-only
			STATUS	current
			::= { hmWanMbus0D 53 }

hmWanMbus0DVIF18		OBJECT-TYPE
			SYNTAX	INTEGER
			MAX-ACCESS	read-only
			STATUS	current
			::= { hmWanMbus0D 54 }

hmWanMbus0DValue18		OBJECT-TYPE
			SYNTAX	INTEGER
			MAX-ACCESS	read-only
			STATUS	current
			::= { hmWanMbus0D 55 }

hmWanMbus0DVIF19		OBJECT-TYPE
			SYNTAX	INTEGER
			MAX-ACCESS	read-only
			STATUS	current
			::= { hmWanMbus0D 56 }

hmWanMbus0DValue19		OBJECT-TYPE
			SYNTAX	INTEGER
			MAX-ACCESS	read-only
			STATUS	current
			::= { hmWanMbus0D 57 }

hmWanMbus0DVIF1A		OBJECT-TYPE
			SYNTAX	INTEGER
			MAX-ACCESS	read-only
			STATUS	current
			::= { hmWanMbus0D 58 }

hmWanMbus0DValue1A		OBJECT-TYPE
			SYNTAX	INTEGER
			MAX-ACCESS	read-only
			STATUS	current
			::= { hmWanMbus0D 59 }

hmWanMbus0DVIF1B		OBJECT-TYPE
			SYNTAX	INTEGER
			MAX-ACCESS	read-only
			STATUS	current
			::= { hmWanMbus0D 60 }

hmWanMbus0DValue1B		OBJECT-TYPE
			SYNTAX	INTEGER
			MAX-ACCESS	read-only
			STATUS	current
			::= { hmWanMbus0D 61 }

hmWanMbus0DVIF1C		OBJECT-TYPE
			SYNTAX	INTEGER
			MAX-ACCESS	read-only
			STATUS	current
			::= { hmWanMbus0D 62 }

hmWanMbus0DValue1C		OBJECT-TYPE
			SYNTAX	INTEGER
			MAX-ACCESS	read-only
			STATUS	current
			::= { hmWanMbus0D 63 }

hmWanMbus0DVIF1D		OBJECT-TYPE
			SYNTAX	INTEGER
			MAX-ACCESS	read-only
			STATUS	current
			::= { hmWanMbus0D 64 }

hmWanMbus0DValue1D		OBJECT-TYPE
			SYNTAX	INTEGER
			MAX-ACCESS	read-only
			STATUS	current
			::= { hmWanMbus0D 65 }

hmWanMbus0DVIF1E		OBJECT-TYPE
			SYNTAX	INTEGER
			MAX-ACCESS	read-only
			STATUS	current
			::= { hmWanMbus0D 66 }

hmWanMbus0DValue1E		OBJECT-TYPE
			SYNTAX	INTEGER
			MAX-ACCESS	read-only
			STATUS	current
			::= { hmWanMbus0D 67 }

hmWanMbus0DVIF1F		OBJECT-TYPE
			SYNTAX	INTEGER
			MAX-ACCESS	read-only
			STATUS	current
			::= { hmWanMbus0D 68 }

hmWanMbus0DValue1F		OBJECT-TYPE
			SYNTAX	INTEGER
			MAX-ACCESS	read-only
			STATUS	current
			::= { hmWanMbus0D 69 }

hmWanMbus0DVIF20		OBJECT-TYPE
			SYNTAX	INTEGER
			MAX-ACCESS	read-only
			STATUS	current
			::= { hmWanMbus0D 70 }

hmWanMbus0DValue20		OBJECT-TYPE
			SYNTAX	INTEGER
			MAX-ACCESS	read-only
			STATUS	current
			::= { hmWanMbus0D 71 }

hmWanMbus0DVIF21		OBJECT-TYPE
			SYNTAX	INTEGER
			MAX-ACCESS	read-only
			STATUS	current
			::= { hmWanMbus0D 72 }

hmWanMbus0DValue21		OBJECT-TYPE
			SYNTAX	INTEGER
			MAX-ACCESS	read-only
			STATUS	current
			::= { hmWanMbus0D 73 }

hmWanMbus0DVIF22		OBJECT-TYPE
			SYNTAX	INTEGER
			MAX-ACCESS	read-only
			STATUS	current
			::= { hmWanMbus0D 74 }

hmWanMbus0DValue22		OBJECT-TYPE
			SYNTAX	INTEGER
			MAX-ACCESS	read-only
			STATUS	current
			::= { hmWanMbus0D 75 }

hmWanMbus0DVIF23		OBJECT-TYPE
			SYNTAX	INTEGER
			MAX-ACCESS	read-only
			STATUS	current
			::= { hmWanMbus0D 76 }

hmWanMbus0DValue23		OBJECT-TYPE
			SYNTAX	INTEGER
			MAX-ACCESS	read-only
			STATUS	current
			::= { hmWanMbus0D 77 }

hmWanMbus0DVIF24		OBJECT-TYPE
			SYNTAX	INTEGER
			MAX-ACCESS	read-only
			STATUS	current
			::= { hmWanMbus0D 78 }

hmWanMbus0DValue24		OBJECT-TYPE
			SYNTAX	INTEGER
			MAX-ACCESS	read-only
			STATUS	current
			::= { hmWanMbus0D 79 }

hmWanMbus0DVIF25		OBJECT-TYPE
			SYNTAX	INTEGER
			MAX-ACCESS	read-only
			STATUS	current
			::= { hmWanMbus0D 80 }

hmWanMbus0DValue25		OBJECT-TYPE
			SYNTAX	INTEGER
			MAX-ACCESS	read-only
			STATUS	current
			::= { hmWanMbus0D 81 }

hmWanMbus0DVIF26		OBJECT-TYPE
			SYNTAX	INTEGER
			MAX-ACCESS	read-only
			STATUS	current
			::= { hmWanMbus0D 82 }

hmWanMbus0DValue26		OBJECT-TYPE
			SYNTAX	INTEGER
			MAX-ACCESS	read-only
			STATUS	current
			::= { hmWanMbus0D 83 }

hmWanMbus0DVIF27		OBJECT-TYPE
			SYNTAX	INTEGER
			MAX-ACCESS	read-only
			STATUS	current
			::= { hmWanMbus0D 84 }

hmWanMbus0DValue27		OBJECT-TYPE
			SYNTAX	INTEGER
			MAX-ACCESS	read-only
			STATUS	current
			::= { hmWanMbus0D 85 }

hmWanMbus0DVIF28		OBJECT-TYPE
			SYNTAX	INTEGER
			MAX-ACCESS	read-only
			STATUS	current
			::= { hmWanMbus0D 86 }

hmWanMbus0DValue28		OBJECT-TYPE
			SYNTAX	INTEGER
			MAX-ACCESS	read-only
			STATUS	current
			::= { hmWanMbus0D 87 }

hmWanMbus0DVIF29		OBJECT-TYPE
			SYNTAX	INTEGER
			MAX-ACCESS	read-only
			STATUS	current
			::= { hmWanMbus0D 88 }

hmWanMbus0DValue29		OBJECT-TYPE
			SYNTAX	INTEGER
			MAX-ACCESS	read-only
			STATUS	current
			::= { hmWanMbus0D 89 }

hmWanMbus0DVIF2A		OBJECT-TYPE
			SYNTAX	INTEGER
			MAX-ACCESS	read-only
			STATUS	current
			::= { hmWanMbus0D 90 }

hmWanMbus0DValue2A		OBJECT-TYPE
			SYNTAX	INTEGER
			MAX-ACCESS	read-only
			STATUS	current
			::= { hmWanMbus0D 91 }

hmWanMbus0DVIF2B		OBJECT-TYPE
			SYNTAX	INTEGER
			MAX-ACCESS	read-only
			STATUS	current
			::= { hmWanMbus0D 92 }

hmWanMbus0DValue2B		OBJECT-TYPE
			SYNTAX	INTEGER
			MAX-ACCESS	read-only
			STATUS	current
			::= { hmWanMbus0D 93 }

hmWanMbus0DVIF2C		OBJECT-TYPE
			SYNTAX	INTEGER
			MAX-ACCESS	read-only
			STATUS	current
			::= { hmWanMbus0D 94 }

hmWanMbus0DValue2C		OBJECT-TYPE
			SYNTAX	INTEGER
			MAX-ACCESS	read-only
			STATUS	current
			::= { hmWanMbus0D 95 }

hmWanMbus0DVIF2D		OBJECT-TYPE
			SYNTAX	INTEGER
			MAX-ACCESS	read-only
			STATUS	current
			::= { hmWanMbus0D 96 }

hmWanMbus0DValue2D		OBJECT-TYPE
			SYNTAX	INTEGER
			MAX-ACCESS	read-only
			STATUS	current
			::= { hmWanMbus0D 97 }

hmWanMbus0DVIF2E		OBJECT-TYPE
			SYNTAX	INTEGER
			MAX-ACCESS	read-only
			STATUS	current
			::= { hmWanMbus0D 98 }

hmWanMbus0DValue2E		OBJECT-TYPE
			SYNTAX	INTEGER
			MAX-ACCESS	read-only
			STATUS	current
			::= { hmWanMbus0D 99 }

hmWanMbus0DVIF2F		OBJECT-TYPE
			SYNTAX	INTEGER
			MAX-ACCESS	read-only
			STATUS	current
			::= { hmWanMbus0D 100 }

hmWanMbus0DValue2F		OBJECT-TYPE
			SYNTAX	INTEGER
			MAX-ACCESS	read-only
			STATUS	current
			::= { hmWanMbus0D 101 }

hmWanMbus0E			OBJECT IDENTIFIER ::= { hmWanMbus 14 }

hmWanMbus0EIdNumber		OBJECT-TYPE
			SYNTAX	Gauge32
			MAX-ACCESS	read-only
			STATUS	current
			::= { hmWanMbus0E 1 }

hmWanMbus0EManufacturer	OBJECT-TYPE
			SYNTAX	Gauge32
			MAX-ACCESS	read-only
			STATUS	current
			::= { hmWanMbus0E 2 }

hmWanMbus0EVersion		OBJECT-TYPE
			SYNTAX	Gauge32
			MAX-ACCESS	read-only
			STATUS	current
			::= { hmWanMbus0E 3 }

hmWanMbus0EMedium		OBJECT-TYPE
			SYNTAX	Gauge32
			MAX-ACCESS	read-only
			STATUS	current
			::= { hmWanMbus0E 4 }

hmWanMbus0EStatus		OBJECT-TYPE
			SYNTAX	Gauge32
			MAX-ACCESS	read-only
			STATUS	current
			::= { hmWanMbus0E 5 }

hmWanMbus0EVIF00		OBJECT-TYPE
			SYNTAX	INTEGER
			MAX-ACCESS	read-only
			STATUS	current
			::= { hmWanMbus0E 6 }

hmWanMbus0EValue00		OBJECT-TYPE
			SYNTAX	INTEGER
			MAX-ACCESS	read-only
			STATUS	current
			::= { hmWanMbus0E 7 }

hmWanMbus0EVIF01		OBJECT-TYPE
			SYNTAX	INTEGER
			MAX-ACCESS	read-only
			STATUS	current
			::= { hmWanMbus0E 8 }

hmWanMbus0EValue01		OBJECT-TYPE
			SYNTAX	INTEGER
			MAX-ACCESS	read-only
			STATUS	current
			::= { hmWanMbus0E 9 }

hmWanMbus0EVIF02		OBJECT-TYPE
			SYNTAX	INTEGER
			MAX-ACCESS	read-only
			STATUS	current
			::= { hmWanMbus0E 10 }

hmWanMbus0EValue02		OBJECT-TYPE
			SYNTAX	INTEGER
			MAX-ACCESS	read-only
			STATUS	current
			::= { hmWanMbus0E 11 }

hmWanMbus0EVIF03		OBJECT-TYPE
			SYNTAX	INTEGER
			MAX-ACCESS	read-only
			STATUS	current
			::= { hmWanMbus0E 12 }

hmWanMbus0EValue03		OBJECT-TYPE
			SYNTAX	INTEGER
			MAX-ACCESS	read-only
			STATUS	current
			::= { hmWanMbus0E 13 }

hmWanMbus0EVIF04		OBJECT-TYPE
			SYNTAX	INTEGER
			MAX-ACCESS	read-only
			STATUS	current
			::= { hmWanMbus0E 14 }

hmWanMbus0EValue04		OBJECT-TYPE
			SYNTAX	INTEGER
			MAX-ACCESS	read-only
			STATUS	current
			::= { hmWanMbus0E 15 }

hmWanMbus0EVIF05		OBJECT-TYPE
			SYNTAX	INTEGER
			MAX-ACCESS	read-only
			STATUS	current
			::= { hmWanMbus0E 16 }

hmWanMbus0EValue05		OBJECT-TYPE
			SYNTAX	INTEGER
			MAX-ACCESS	read-only
			STATUS	current
			::= { hmWanMbus0E 17 }

hmWanMbus0EVIF06		OBJECT-TYPE
			SYNTAX	INTEGER
			MAX-ACCESS	read-only
			STATUS	current
			::= { hmWanMbus0E 18 }

hmWanMbus0EValue06		OBJECT-TYPE
			SYNTAX	INTEGER
			MAX-ACCESS	read-only
			STATUS	current
			::= { hmWanMbus0E 19 }

hmWanMbus0EVIF07		OBJECT-TYPE
			SYNTAX	INTEGER
			MAX-ACCESS	read-only
			STATUS	current
			::= { hmWanMbus0E 20 }

hmWanMbus0EValue07		OBJECT-TYPE
			SYNTAX	INTEGER
			MAX-ACCESS	read-only
			STATUS	current
			::= { hmWanMbus0E 21 }

hmWanMbus0EVIF08		OBJECT-TYPE
			SYNTAX	INTEGER
			MAX-ACCESS	read-only
			STATUS	current
			::= { hmWanMbus0E 22 }

hmWanMbus0EValue08		OBJECT-TYPE
			SYNTAX	INTEGER
			MAX-ACCESS	read-only
			STATUS	current
			::= { hmWanMbus0E 23 }

hmWanMbus0EVIF09		OBJECT-TYPE
			SYNTAX	INTEGER
			MAX-ACCESS	read-only
			STATUS	current
			::= { hmWanMbus0E 24 }

hmWanMbus0EValue09		OBJECT-TYPE
			SYNTAX	INTEGER
			MAX-ACCESS	read-only
			STATUS	current
			::= { hmWanMbus0E 25 }

hmWanMbus0EVIF0A		OBJECT-TYPE
			SYNTAX	INTEGER
			MAX-ACCESS	read-only
			STATUS	current
			::= { hmWanMbus0E 26 }

hmWanMbus0EValue0A		OBJECT-TYPE
			SYNTAX	INTEGER
			MAX-ACCESS	read-only
			STATUS	current
			::= { hmWanMbus0E 27 }

hmWanMbus0EVIF0B		OBJECT-TYPE
			SYNTAX	INTEGER
			MAX-ACCESS	read-only
			STATUS	current
			::= { hmWanMbus0E 28 }

hmWanMbus0EValue0B		OBJECT-TYPE
			SYNTAX	INTEGER
			MAX-ACCESS	read-only
			STATUS	current
			::= { hmWanMbus0E 29 }

hmWanMbus0EVIF0C		OBJECT-TYPE
			SYNTAX	INTEGER
			MAX-ACCESS	read-only
			STATUS	current
			::= { hmWanMbus0E 30 }

hmWanMbus0EValue0C		OBJECT-TYPE
			SYNTAX	INTEGER
			MAX-ACCESS	read-only
			STATUS	current
			::= { hmWanMbus0E 31 }

hmWanMbus0EVIF0D		OBJECT-TYPE
			SYNTAX	INTEGER
			MAX-ACCESS	read-only
			STATUS	current
			::= { hmWanMbus0E 32 }

hmWanMbus0EValue0D		OBJECT-TYPE
			SYNTAX	INTEGER
			MAX-ACCESS	read-only
			STATUS	current
			::= { hmWanMbus0E 33 }

hmWanMbus0EVIF0E		OBJECT-TYPE
			SYNTAX	INTEGER
			MAX-ACCESS	read-only
			STATUS	current
			::= { hmWanMbus0E 34 }

hmWanMbus0EValue0E		OBJECT-TYPE
			SYNTAX	INTEGER
			MAX-ACCESS	read-only
			STATUS	current
			::= { hmWanMbus0E 35 }

hmWanMbus0EVIF0F		OBJECT-TYPE
			SYNTAX	INTEGER
			MAX-ACCESS	read-only
			STATUS	current
			::= { hmWanMbus0E 36 }

hmWanMbus0EValue0F		OBJECT-TYPE
			SYNTAX	INTEGER
			MAX-ACCESS	read-only
			STATUS	current
			::= { hmWanMbus0E 37 }

hmWanMbus0EVIF10		OBJECT-TYPE
			SYNTAX	INTEGER
			MAX-ACCESS	read-only
			STATUS	current
			::= { hmWanMbus0E 38 }

hmWanMbus0EValue10		OBJECT-TYPE
			SYNTAX	INTEGER
			MAX-ACCESS	read-only
			STATUS	current
			::= { hmWanMbus0E 39 }

hmWanMbus0EVIF11		OBJECT-TYPE
			SYNTAX	INTEGER
			MAX-ACCESS	read-only
			STATUS	current
			::= { hmWanMbus0E 40 }

hmWanMbus0EValue11		OBJECT-TYPE
			SYNTAX	INTEGER
			MAX-ACCESS	read-only
			STATUS	current
			::= { hmWanMbus0E 41 }

hmWanMbus0EVIF12		OBJECT-TYPE
			SYNTAX	INTEGER
			MAX-ACCESS	read-only
			STATUS	current
			::= { hmWanMbus0E 42 }

hmWanMbus0EValue12		OBJECT-TYPE
			SYNTAX	INTEGER
			MAX-ACCESS	read-only
			STATUS	current
			::= { hmWanMbus0E 43 }

hmWanMbus0EVIF13		OBJECT-TYPE
			SYNTAX	INTEGER
			MAX-ACCESS	read-only
			STATUS	current
			::= { hmWanMbus0E 44 }

hmWanMbus0EValue13		OBJECT-TYPE
			SYNTAX	INTEGER
			MAX-ACCESS	read-only
			STATUS	current
			::= { hmWanMbus0E 45 }

hmWanMbus0EVIF14		OBJECT-TYPE
			SYNTAX	INTEGER
			MAX-ACCESS	read-only
			STATUS	current
			::= { hmWanMbus0E 46 }

hmWanMbus0EValue14		OBJECT-TYPE
			SYNTAX	INTEGER
			MAX-ACCESS	read-only
			STATUS	current
			::= { hmWanMbus0E 47 }

hmWanMbus0EVIF15		OBJECT-TYPE
			SYNTAX	INTEGER
			MAX-ACCESS	read-only
			STATUS	current
			::= { hmWanMbus0E 48 }

hmWanMbus0EValue15		OBJECT-TYPE
			SYNTAX	INTEGER
			MAX-ACCESS	read-only
			STATUS	current
			::= { hmWanMbus0E 49 }

hmWanMbus0EVIF16		OBJECT-TYPE
			SYNTAX	INTEGER
			MAX-ACCESS	read-only
			STATUS	current
			::= { hmWanMbus0E 50 }

hmWanMbus0EValue16		OBJECT-TYPE
			SYNTAX	INTEGER
			MAX-ACCESS	read-only
			STATUS	current
			::= { hmWanMbus0E 51 }

hmWanMbus0EVIF17		OBJECT-TYPE
			SYNTAX	INTEGER
			MAX-ACCESS	read-only
			STATUS	current
			::= { hmWanMbus0E 52 }

hmWanMbus0EValue17		OBJECT-TYPE
			SYNTAX	INTEGER
			MAX-ACCESS	read-only
			STATUS	current
			::= { hmWanMbus0E 53 }

hmWanMbus0EVIF18		OBJECT-TYPE
			SYNTAX	INTEGER
			MAX-ACCESS	read-only
			STATUS	current
			::= { hmWanMbus0E 54 }

hmWanMbus0EValue18		OBJECT-TYPE
			SYNTAX	INTEGER
			MAX-ACCESS	read-only
			STATUS	current
			::= { hmWanMbus0E 55 }

hmWanMbus0EVIF19		OBJECT-TYPE
			SYNTAX	INTEGER
			MAX-ACCESS	read-only
			STATUS	current
			::= { hmWanMbus0E 56 }

hmWanMbus0EValue19		OBJECT-TYPE
			SYNTAX	INTEGER
			MAX-ACCESS	read-only
			STATUS	current
			::= { hmWanMbus0E 57 }

hmWanMbus0EVIF1A		OBJECT-TYPE
			SYNTAX	INTEGER
			MAX-ACCESS	read-only
			STATUS	current
			::= { hmWanMbus0E 58 }

hmWanMbus0EValue1A		OBJECT-TYPE
			SYNTAX	INTEGER
			MAX-ACCESS	read-only
			STATUS	current
			::= { hmWanMbus0E 59 }

hmWanMbus0EVIF1B		OBJECT-TYPE
			SYNTAX	INTEGER
			MAX-ACCESS	read-only
			STATUS	current
			::= { hmWanMbus0E 60 }

hmWanMbus0EValue1B		OBJECT-TYPE
			SYNTAX	INTEGER
			MAX-ACCESS	read-only
			STATUS	current
			::= { hmWanMbus0E 61 }

hmWanMbus0EVIF1C		OBJECT-TYPE
			SYNTAX	INTEGER
			MAX-ACCESS	read-only
			STATUS	current
			::= { hmWanMbus0E 62 }

hmWanMbus0EValue1C		OBJECT-TYPE
			SYNTAX	INTEGER
			MAX-ACCESS	read-only
			STATUS	current
			::= { hmWanMbus0E 63 }

hmWanMbus0EVIF1D		OBJECT-TYPE
			SYNTAX	INTEGER
			MAX-ACCESS	read-only
			STATUS	current
			::= { hmWanMbus0E 64 }

hmWanMbus0EValue1D		OBJECT-TYPE
			SYNTAX	INTEGER
			MAX-ACCESS	read-only
			STATUS	current
			::= { hmWanMbus0E 65 }

hmWanMbus0EVIF1E		OBJECT-TYPE
			SYNTAX	INTEGER
			MAX-ACCESS	read-only
			STATUS	current
			::= { hmWanMbus0E 66 }

hmWanMbus0EValue1E		OBJECT-TYPE
			SYNTAX	INTEGER
			MAX-ACCESS	read-only
			STATUS	current
			::= { hmWanMbus0E 67 }

hmWanMbus0EVIF1F		OBJECT-TYPE
			SYNTAX	INTEGER
			MAX-ACCESS	read-only
			STATUS	current
			::= { hmWanMbus0E 68 }

hmWanMbus0EValue1F		OBJECT-TYPE
			SYNTAX	INTEGER
			MAX-ACCESS	read-only
			STATUS	current
			::= { hmWanMbus0E 69 }

hmWanMbus0EVIF20		OBJECT-TYPE
			SYNTAX	INTEGER
			MAX-ACCESS	read-only
			STATUS	current
			::= { hmWanMbus0E 70 }

hmWanMbus0EValue20		OBJECT-TYPE
			SYNTAX	INTEGER
			MAX-ACCESS	read-only
			STATUS	current
			::= { hmWanMbus0E 71 }

hmWanMbus0EVIF21		OBJECT-TYPE
			SYNTAX	INTEGER
			MAX-ACCESS	read-only
			STATUS	current
			::= { hmWanMbus0E 72 }

hmWanMbus0EValue21		OBJECT-TYPE
			SYNTAX	INTEGER
			MAX-ACCESS	read-only
			STATUS	current
			::= { hmWanMbus0E 73 }

hmWanMbus0EVIF22		OBJECT-TYPE
			SYNTAX	INTEGER
			MAX-ACCESS	read-only
			STATUS	current
			::= { hmWanMbus0E 74 }

hmWanMbus0EValue22		OBJECT-TYPE
			SYNTAX	INTEGER
			MAX-ACCESS	read-only
			STATUS	current
			::= { hmWanMbus0E 75 }

hmWanMbus0EVIF23		OBJECT-TYPE
			SYNTAX	INTEGER
			MAX-ACCESS	read-only
			STATUS	current
			::= { hmWanMbus0E 76 }

hmWanMbus0EValue23		OBJECT-TYPE
			SYNTAX	INTEGER
			MAX-ACCESS	read-only
			STATUS	current
			::= { hmWanMbus0E 77 }

hmWanMbus0EVIF24		OBJECT-TYPE
			SYNTAX	INTEGER
			MAX-ACCESS	read-only
			STATUS	current
			::= { hmWanMbus0E 78 }

hmWanMbus0EValue24		OBJECT-TYPE
			SYNTAX	INTEGER
			MAX-ACCESS	read-only
			STATUS	current
			::= { hmWanMbus0E 79 }

hmWanMbus0EVIF25		OBJECT-TYPE
			SYNTAX	INTEGER
			MAX-ACCESS	read-only
			STATUS	current
			::= { hmWanMbus0E 80 }

hmWanMbus0EValue25		OBJECT-TYPE
			SYNTAX	INTEGER
			MAX-ACCESS	read-only
			STATUS	current
			::= { hmWanMbus0E 81 }

hmWanMbus0EVIF26		OBJECT-TYPE
			SYNTAX	INTEGER
			MAX-ACCESS	read-only
			STATUS	current
			::= { hmWanMbus0E 82 }

hmWanMbus0EValue26		OBJECT-TYPE
			SYNTAX	INTEGER
			MAX-ACCESS	read-only
			STATUS	current
			::= { hmWanMbus0E 83 }

hmWanMbus0EVIF27		OBJECT-TYPE
			SYNTAX	INTEGER
			MAX-ACCESS	read-only
			STATUS	current
			::= { hmWanMbus0E 84 }

hmWanMbus0EValue27		OBJECT-TYPE
			SYNTAX	INTEGER
			MAX-ACCESS	read-only
			STATUS	current
			::= { hmWanMbus0E 85 }

hmWanMbus0EVIF28		OBJECT-TYPE
			SYNTAX	INTEGER
			MAX-ACCESS	read-only
			STATUS	current
			::= { hmWanMbus0E 86 }

hmWanMbus0EValue28		OBJECT-TYPE
			SYNTAX	INTEGER
			MAX-ACCESS	read-only
			STATUS	current
			::= { hmWanMbus0E 87 }

hmWanMbus0EVIF29		OBJECT-TYPE
			SYNTAX	INTEGER
			MAX-ACCESS	read-only
			STATUS	current
			::= { hmWanMbus0E 88 }

hmWanMbus0EValue29		OBJECT-TYPE
			SYNTAX	INTEGER
			MAX-ACCESS	read-only
			STATUS	current
			::= { hmWanMbus0E 89 }

hmWanMbus0EVIF2A		OBJECT-TYPE
			SYNTAX	INTEGER
			MAX-ACCESS	read-only
			STATUS	current
			::= { hmWanMbus0E 90 }

hmWanMbus0EValue2A		OBJECT-TYPE
			SYNTAX	INTEGER
			MAX-ACCESS	read-only
			STATUS	current
			::= { hmWanMbus0E 91 }

hmWanMbus0EVIF2B		OBJECT-TYPE
			SYNTAX	INTEGER
			MAX-ACCESS	read-only
			STATUS	current
			::= { hmWanMbus0E 92 }

hmWanMbus0EValue2B		OBJECT-TYPE
			SYNTAX	INTEGER
			MAX-ACCESS	read-only
			STATUS	current
			::= { hmWanMbus0E 93 }

hmWanMbus0EVIF2C		OBJECT-TYPE
			SYNTAX	INTEGER
			MAX-ACCESS	read-only
			STATUS	current
			::= { hmWanMbus0E 94 }

hmWanMbus0EValue2C		OBJECT-TYPE
			SYNTAX	INTEGER
			MAX-ACCESS	read-only
			STATUS	current
			::= { hmWanMbus0E 95 }

hmWanMbus0EVIF2D		OBJECT-TYPE
			SYNTAX	INTEGER
			MAX-ACCESS	read-only
			STATUS	current
			::= { hmWanMbus0E 96 }

hmWanMbus0EValue2D		OBJECT-TYPE
			SYNTAX	INTEGER
			MAX-ACCESS	read-only
			STATUS	current
			::= { hmWanMbus0E 97 }

hmWanMbus0EVIF2E		OBJECT-TYPE
			SYNTAX	INTEGER
			MAX-ACCESS	read-only
			STATUS	current
			::= { hmWanMbus0E 98 }

hmWanMbus0EValue2E		OBJECT-TYPE
			SYNTAX	INTEGER
			MAX-ACCESS	read-only
			STATUS	current
			::= { hmWanMbus0E 99 }

hmWanMbus0EVIF2F		OBJECT-TYPE
			SYNTAX	INTEGER
			MAX-ACCESS	read-only
			STATUS	current
			::= { hmWanMbus0E 100 }

hmWanMbus0EValue2F		OBJECT-TYPE
			SYNTAX	INTEGER
			MAX-ACCESS	read-only
			STATUS	current
			::= { hmWanMbus0E 101 }

hmWanMbus0F			OBJECT IDENTIFIER ::= { hmWanMbus 15 }

hmWanMbus0FIdNumber		OBJECT-TYPE
			SYNTAX	Gauge32
			MAX-ACCESS	read-only
			STATUS	current
			::= { hmWanMbus0F 1 }

hmWanMbus0FManufacturer	OBJECT-TYPE
			SYNTAX	Gauge32
			MAX-ACCESS	read-only
			STATUS	current
			::= { hmWanMbus0F 2 }

hmWanMbus0FVersion		OBJECT-TYPE
			SYNTAX	Gauge32
			MAX-ACCESS	read-only
			STATUS	current
			::= { hmWanMbus0F 3 }

hmWanMbus0FMedium		OBJECT-TYPE
			SYNTAX	Gauge32
			MAX-ACCESS	read-only
			STATUS	current
			::= { hmWanMbus0F 4 }

hmWanMbus0FStatus		OBJECT-TYPE
			SYNTAX	Gauge32
			MAX-ACCESS	read-only
			STATUS	current
			::= { hmWanMbus0F 5 }

hmWanMbus0FVIF00		OBJECT-TYPE
			SYNTAX	INTEGER
			MAX-ACCESS	read-only
			STATUS	current
			::= { hmWanMbus0F 6 }

hmWanMbus0FValue00		OBJECT-TYPE
			SYNTAX	INTEGER
			MAX-ACCESS	read-only
			STATUS	current
			::= { hmWanMbus0F 7 }

hmWanMbus0FVIF01		OBJECT-TYPE
			SYNTAX	INTEGER
			MAX-ACCESS	read-only
			STATUS	current
			::= { hmWanMbus0F 8 }

hmWanMbus0FValue01		OBJECT-TYPE
			SYNTAX	INTEGER
			MAX-ACCESS	read-only
			STATUS	current
			::= { hmWanMbus0F 9 }

hmWanMbus0FVIF02		OBJECT-TYPE
			SYNTAX	INTEGER
			MAX-ACCESS	read-only
			STATUS	current
			::= { hmWanMbus0F 10 }

hmWanMbus0FValue02		OBJECT-TYPE
			SYNTAX	INTEGER
			MAX-ACCESS	read-only
			STATUS	current
			::= { hmWanMbus0F 11 }

hmWanMbus0FVIF03		OBJECT-TYPE
			SYNTAX	INTEGER
			MAX-ACCESS	read-only
			STATUS	current
			::= { hmWanMbus0F 12 }

hmWanMbus0FValue03		OBJECT-TYPE
			SYNTAX	INTEGER
			MAX-ACCESS	read-only
			STATUS	current
			::= { hmWanMbus0F 13 }

hmWanMbus0FVIF04		OBJECT-TYPE
			SYNTAX	INTEGER
			MAX-ACCESS	read-only
			STATUS	current
			::= { hmWanMbus0F 14 }

hmWanMbus0FValue04		OBJECT-TYPE
			SYNTAX	INTEGER
			MAX-ACCESS	read-only
			STATUS	current
			::= { hmWanMbus0F 15 }

hmWanMbus0FVIF05		OBJECT-TYPE
			SYNTAX	INTEGER
			MAX-ACCESS	read-only
			STATUS	current
			::= { hmWanMbus0F 16 }

hmWanMbus0FValue05		OBJECT-TYPE
			SYNTAX	INTEGER
			MAX-ACCESS	read-only
			STATUS	current
			::= { hmWanMbus0F 17 }

hmWanMbus0FVIF06		OBJECT-TYPE
			SYNTAX	INTEGER
			MAX-ACCESS	read-only
			STATUS	current
			::= { hmWanMbus0F 18 }

hmWanMbus0FValue06		OBJECT-TYPE
			SYNTAX	INTEGER
			MAX-ACCESS	read-only
			STATUS	current
			::= { hmWanMbus0F 19 }

hmWanMbus0FVIF07		OBJECT-TYPE
			SYNTAX	INTEGER
			MAX-ACCESS	read-only
			STATUS	current
			::= { hmWanMbus0F 20 }

hmWanMbus0FValue07		OBJECT-TYPE
			SYNTAX	INTEGER
			MAX-ACCESS	read-only
			STATUS	current
			::= { hmWanMbus0F 21 }

hmWanMbus0FVIF08		OBJECT-TYPE
			SYNTAX	INTEGER
			MAX-ACCESS	read-only
			STATUS	current
			::= { hmWanMbus0F 22 }

hmWanMbus0FValue08		OBJECT-TYPE
			SYNTAX	INTEGER
			MAX-ACCESS	read-only
			STATUS	current
			::= { hmWanMbus0F 23 }

hmWanMbus0FVIF09		OBJECT-TYPE
			SYNTAX	INTEGER
			MAX-ACCESS	read-only
			STATUS	current
			::= { hmWanMbus0F 24 }

hmWanMbus0FValue09		OBJECT-TYPE
			SYNTAX	INTEGER
			MAX-ACCESS	read-only
			STATUS	current
			::= { hmWanMbus0F 25 }

hmWanMbus0FVIF0A		OBJECT-TYPE
			SYNTAX	INTEGER
			MAX-ACCESS	read-only
			STATUS	current
			::= { hmWanMbus0F 26 }

hmWanMbus0FValue0A		OBJECT-TYPE
			SYNTAX	INTEGER
			MAX-ACCESS	read-only
			STATUS	current
			::= { hmWanMbus0F 27 }

hmWanMbus0FVIF0B		OBJECT-TYPE
			SYNTAX	INTEGER
			MAX-ACCESS	read-only
			STATUS	current
			::= { hmWanMbus0F 28 }

hmWanMbus0FValue0B		OBJECT-TYPE
			SYNTAX	INTEGER
			MAX-ACCESS	read-only
			STATUS	current
			::= { hmWanMbus0F 29 }

hmWanMbus0FVIF0C		OBJECT-TYPE
			SYNTAX	INTEGER
			MAX-ACCESS	read-only
			STATUS	current
			::= { hmWanMbus0F 30 }

hmWanMbus0FValue0C		OBJECT-TYPE
			SYNTAX	INTEGER
			MAX-ACCESS	read-only
			STATUS	current
			::= { hmWanMbus0F 31 }

hmWanMbus0FVIF0D		OBJECT-TYPE
			SYNTAX	INTEGER
			MAX-ACCESS	read-only
			STATUS	current
			::= { hmWanMbus0F 32 }

hmWanMbus0FValue0D		OBJECT-TYPE
			SYNTAX	INTEGER
			MAX-ACCESS	read-only
			STATUS	current
			::= { hmWanMbus0F 33 }

hmWanMbus0FVIF0E		OBJECT-TYPE
			SYNTAX	INTEGER
			MAX-ACCESS	read-only
			STATUS	current
			::= { hmWanMbus0F 34 }

hmWanMbus0FValue0E		OBJECT-TYPE
			SYNTAX	INTEGER
			MAX-ACCESS	read-only
			STATUS	current
			::= { hmWanMbus0F 35 }

hmWanMbus0FVIF0F		OBJECT-TYPE
			SYNTAX	INTEGER
			MAX-ACCESS	read-only
			STATUS	current
			::= { hmWanMbus0F 36 }

hmWanMbus0FValue0F		OBJECT-TYPE
			SYNTAX	INTEGER
			MAX-ACCESS	read-only
			STATUS	current
			::= { hmWanMbus0F 37 }

hmWanMbus0FVIF10		OBJECT-TYPE
			SYNTAX	INTEGER
			MAX-ACCESS	read-only
			STATUS	current
			::= { hmWanMbus0F 38 }

hmWanMbus0FValue10		OBJECT-TYPE
			SYNTAX	INTEGER
			MAX-ACCESS	read-only
			STATUS	current
			::= { hmWanMbus0F 39 }

hmWanMbus0FVIF11		OBJECT-TYPE
			SYNTAX	INTEGER
			MAX-ACCESS	read-only
			STATUS	current
			::= { hmWanMbus0F 40 }

hmWanMbus0FValue11		OBJECT-TYPE
			SYNTAX	INTEGER
			MAX-ACCESS	read-only
			STATUS	current
			::= { hmWanMbus0F 41 }

hmWanMbus0FVIF12		OBJECT-TYPE
			SYNTAX	INTEGER
			MAX-ACCESS	read-only
			STATUS	current
			::= { hmWanMbus0F 42 }

hmWanMbus0FValue12		OBJECT-TYPE
			SYNTAX	INTEGER
			MAX-ACCESS	read-only
			STATUS	current
			::= { hmWanMbus0F 43 }

hmWanMbus0FVIF13		OBJECT-TYPE
			SYNTAX	INTEGER
			MAX-ACCESS	read-only
			STATUS	current
			::= { hmWanMbus0F 44 }

hmWanMbus0FValue13		OBJECT-TYPE
			SYNTAX	INTEGER
			MAX-ACCESS	read-only
			STATUS	current
			::= { hmWanMbus0F 45 }

hmWanMbus0FVIF14		OBJECT-TYPE
			SYNTAX	INTEGER
			MAX-ACCESS	read-only
			STATUS	current
			::= { hmWanMbus0F 46 }

hmWanMbus0FValue14		OBJECT-TYPE
			SYNTAX	INTEGER
			MAX-ACCESS	read-only
			STATUS	current
			::= { hmWanMbus0F 47 }

hmWanMbus0FVIF15		OBJECT-TYPE
			SYNTAX	INTEGER
			MAX-ACCESS	read-only
			STATUS	current
			::= { hmWanMbus0F 48 }

hmWanMbus0FValue15		OBJECT-TYPE
			SYNTAX	INTEGER
			MAX-ACCESS	read-only
			STATUS	current
			::= { hmWanMbus0F 49 }

hmWanMbus0FVIF16		OBJECT-TYPE
			SYNTAX	INTEGER
			MAX-ACCESS	read-only
			STATUS	current
			::= { hmWanMbus0F 50 }

hmWanMbus0FValue16		OBJECT-TYPE
			SYNTAX	INTEGER
			MAX-ACCESS	read-only
			STATUS	current
			::= { hmWanMbus0F 51 }

hmWanMbus0FVIF17		OBJECT-TYPE
			SYNTAX	INTEGER
			MAX-ACCESS	read-only
			STATUS	current
			::= { hmWanMbus0F 52 }

hmWanMbus0FValue17		OBJECT-TYPE
			SYNTAX	INTEGER
			MAX-ACCESS	read-only
			STATUS	current
			::= { hmWanMbus0F 53 }

hmWanMbus0FVIF18		OBJECT-TYPE
			SYNTAX	INTEGER
			MAX-ACCESS	read-only
			STATUS	current
			::= { hmWanMbus0F 54 }

hmWanMbus0FValue18		OBJECT-TYPE
			SYNTAX	INTEGER
			MAX-ACCESS	read-only
			STATUS	current
			::= { hmWanMbus0F 55 }

hmWanMbus0FVIF19		OBJECT-TYPE
			SYNTAX	INTEGER
			MAX-ACCESS	read-only
			STATUS	current
			::= { hmWanMbus0F 56 }

hmWanMbus0FValue19		OBJECT-TYPE
			SYNTAX	INTEGER
			MAX-ACCESS	read-only
			STATUS	current
			::= { hmWanMbus0F 57 }

hmWanMbus0FVIF1A		OBJECT-TYPE
			SYNTAX	INTEGER
			MAX-ACCESS	read-only
			STATUS	current
			::= { hmWanMbus0F 58 }

hmWanMbus0FValue1A		OBJECT-TYPE
			SYNTAX	INTEGER
			MAX-ACCESS	read-only
			STATUS	current
			::= { hmWanMbus0F 59 }

hmWanMbus0FVIF1B		OBJECT-TYPE
			SYNTAX	INTEGER
			MAX-ACCESS	read-only
			STATUS	current
			::= { hmWanMbus0F 60 }

hmWanMbus0FValue1B		OBJECT-TYPE
			SYNTAX	INTEGER
			MAX-ACCESS	read-only
			STATUS	current
			::= { hmWanMbus0F 61 }

hmWanMbus0FVIF1C		OBJECT-TYPE
			SYNTAX	INTEGER
			MAX-ACCESS	read-only
			STATUS	current
			::= { hmWanMbus0F 62 }

hmWanMbus0FValue1C		OBJECT-TYPE
			SYNTAX	INTEGER
			MAX-ACCESS	read-only
			STATUS	current
			::= { hmWanMbus0F 63 }

hmWanMbus0FVIF1D		OBJECT-TYPE
			SYNTAX	INTEGER
			MAX-ACCESS	read-only
			STATUS	current
			::= { hmWanMbus0F 64 }

hmWanMbus0FValue1D		OBJECT-TYPE
			SYNTAX	INTEGER
			MAX-ACCESS	read-only
			STATUS	current
			::= { hmWanMbus0F 65 }

hmWanMbus0FVIF1E		OBJECT-TYPE
			SYNTAX	INTEGER
			MAX-ACCESS	read-only
			STATUS	current
			::= { hmWanMbus0F 66 }

hmWanMbus0FValue1E		OBJECT-TYPE
			SYNTAX	INTEGER
			MAX-ACCESS	read-only
			STATUS	current
			::= { hmWanMbus0F 67 }

hmWanMbus0FVIF1F		OBJECT-TYPE
			SYNTAX	INTEGER
			MAX-ACCESS	read-only
			STATUS	current
			::= { hmWanMbus0F 68 }

hmWanMbus0FValue1F		OBJECT-TYPE
			SYNTAX	INTEGER
			MAX-ACCESS	read-only
			STATUS	current
			::= { hmWanMbus0F 69 }

hmWanMbus0FVIF20		OBJECT-TYPE
			SYNTAX	INTEGER
			MAX-ACCESS	read-only
			STATUS	current
			::= { hmWanMbus0F 70 }

hmWanMbus0FValue20		OBJECT-TYPE
			SYNTAX	INTEGER
			MAX-ACCESS	read-only
			STATUS	current
			::= { hmWanMbus0F 71 }

hmWanMbus0FVIF21		OBJECT-TYPE
			SYNTAX	INTEGER
			MAX-ACCESS	read-only
			STATUS	current
			::= { hmWanMbus0F 72 }

hmWanMbus0FValue21		OBJECT-TYPE
			SYNTAX	INTEGER
			MAX-ACCESS	read-only
			STATUS	current
			::= { hmWanMbus0F 73 }

hmWanMbus0FVIF22		OBJECT-TYPE
			SYNTAX	INTEGER
			MAX-ACCESS	read-only
			STATUS	current
			::= { hmWanMbus0F 74 }

hmWanMbus0FValue22		OBJECT-TYPE
			SYNTAX	INTEGER
			MAX-ACCESS	read-only
			STATUS	current
			::= { hmWanMbus0F 75 }

hmWanMbus0FVIF23		OBJECT-TYPE
			SYNTAX	INTEGER
			MAX-ACCESS	read-only
			STATUS	current
			::= { hmWanMbus0F 76 }

hmWanMbus0FValue23		OBJECT-TYPE
			SYNTAX	INTEGER
			MAX-ACCESS	read-only
			STATUS	current
			::= { hmWanMbus0F 77 }

hmWanMbus0FVIF24		OBJECT-TYPE
			SYNTAX	INTEGER
			MAX-ACCESS	read-only
			STATUS	current
			::= { hmWanMbus0F 78 }

hmWanMbus0FValue24		OBJECT-TYPE
			SYNTAX	INTEGER
			MAX-ACCESS	read-only
			STATUS	current
			::= { hmWanMbus0F 79 }

hmWanMbus0FVIF25		OBJECT-TYPE
			SYNTAX	INTEGER
			MAX-ACCESS	read-only
			STATUS	current
			::= { hmWanMbus0F 80 }

hmWanMbus0FValue25		OBJECT-TYPE
			SYNTAX	INTEGER
			MAX-ACCESS	read-only
			STATUS	current
			::= { hmWanMbus0F 81 }

hmWanMbus0FVIF26		OBJECT-TYPE
			SYNTAX	INTEGER
			MAX-ACCESS	read-only
			STATUS	current
			::= { hmWanMbus0F 82 }

hmWanMbus0FValue26		OBJECT-TYPE
			SYNTAX	INTEGER
			MAX-ACCESS	read-only
			STATUS	current
			::= { hmWanMbus0F 83 }

hmWanMbus0FVIF27		OBJECT-TYPE
			SYNTAX	INTEGER
			MAX-ACCESS	read-only
			STATUS	current
			::= { hmWanMbus0F 84 }

hmWanMbus0FValue27		OBJECT-TYPE
			SYNTAX	INTEGER
			MAX-ACCESS	read-only
			STATUS	current
			::= { hmWanMbus0F 85 }

hmWanMbus0FVIF28		OBJECT-TYPE
			SYNTAX	INTEGER
			MAX-ACCESS	read-only
			STATUS	current
			::= { hmWanMbus0F 86 }

hmWanMbus0FValue28		OBJECT-TYPE
			SYNTAX	INTEGER
			MAX-ACCESS	read-only
			STATUS	current
			::= { hmWanMbus0F 87 }

hmWanMbus0FVIF29		OBJECT-TYPE
			SYNTAX	INTEGER
			MAX-ACCESS	read-only
			STATUS	current
			::= { hmWanMbus0F 88 }

hmWanMbus0FValue29		OBJECT-TYPE
			SYNTAX	INTEGER
			MAX-ACCESS	read-only
			STATUS	current
			::= { hmWanMbus0F 89 }

hmWanMbus0FVIF2A		OBJECT-TYPE
			SYNTAX	INTEGER
			MAX-ACCESS	read-only
			STATUS	current
			::= { hmWanMbus0F 90 }

hmWanMbus0FValue2A		OBJECT-TYPE
			SYNTAX	INTEGER
			MAX-ACCESS	read-only
			STATUS	current
			::= { hmWanMbus0F 91 }

hmWanMbus0FVIF2B		OBJECT-TYPE
			SYNTAX	INTEGER
			MAX-ACCESS	read-only
			STATUS	current
			::= { hmWanMbus0F 92 }

hmWanMbus0FValue2B		OBJECT-TYPE
			SYNTAX	INTEGER
			MAX-ACCESS	read-only
			STATUS	current
			::= { hmWanMbus0F 93 }

hmWanMbus0FVIF2C		OBJECT-TYPE
			SYNTAX	INTEGER
			MAX-ACCESS	read-only
			STATUS	current
			::= { hmWanMbus0F 94 }

hmWanMbus0FValue2C		OBJECT-TYPE
			SYNTAX	INTEGER
			MAX-ACCESS	read-only
			STATUS	current
			::= { hmWanMbus0F 95 }

hmWanMbus0FVIF2D		OBJECT-TYPE
			SYNTAX	INTEGER
			MAX-ACCESS	read-only
			STATUS	current
			::= { hmWanMbus0F 96 }

hmWanMbus0FValue2D		OBJECT-TYPE
			SYNTAX	INTEGER
			MAX-ACCESS	read-only
			STATUS	current
			::= { hmWanMbus0F 97 }

hmWanMbus0FVIF2E		OBJECT-TYPE
			SYNTAX	INTEGER
			MAX-ACCESS	read-only
			STATUS	current
			::= { hmWanMbus0F 98 }

hmWanMbus0FValue2E		OBJECT-TYPE
			SYNTAX	INTEGER
			MAX-ACCESS	read-only
			STATUS	current
			::= { hmWanMbus0F 99 }

hmWanMbus0FVIF2F		OBJECT-TYPE
			SYNTAX	INTEGER
			MAX-ACCESS	read-only
			STATUS	current
			::= { hmWanMbus0F 100 }

hmWanMbus0FValue2F		OBJECT-TYPE
			SYNTAX	INTEGER
			MAX-ACCESS	read-only
			STATUS	current
			::= { hmWanMbus0F 101 }

hmWanMbus10			OBJECT IDENTIFIER ::= { hmWanMbus 16 }

hmWanMbus10IdNumber		OBJECT-TYPE
			SYNTAX	Gauge32
			MAX-ACCESS	read-only
			STATUS	current
			::= { hmWanMbus10 1 }

hmWanMbus10Manufacturer	OBJECT-TYPE
			SYNTAX	Gauge32
			MAX-ACCESS	read-only
			STATUS	current
			::= { hmWanMbus10 2 }

hmWanMbus10Version		OBJECT-TYPE
			SYNTAX	Gauge32
			MAX-ACCESS	read-only
			STATUS	current
			::= { hmWanMbus10 3 }

hmWanMbus10Medium		OBJECT-TYPE
			SYNTAX	Gauge32
			MAX-ACCESS	read-only
			STATUS	current
			::= { hmWanMbus10 4 }

hmWanMbus10Status		OBJECT-TYPE
			SYNTAX	Gauge32
			MAX-ACCESS	read-only
			STATUS	current
			::= { hmWanMbus10 5 }

hmWanMbus10VIF00		OBJECT-TYPE
			SYNTAX	INTEGER
			MAX-ACCESS	read-only
			STATUS	current
			::= { hmWanMbus10 6 }

hmWanMbus10Value00		OBJECT-TYPE
			SYNTAX	INTEGER
			MAX-ACCESS	read-only
			STATUS	current
			::= { hmWanMbus10 7 }

hmWanMbus10VIF01		OBJECT-TYPE
			SYNTAX	INTEGER
			MAX-ACCESS	read-only
			STATUS	current
			::= { hmWanMbus10 8 }

hmWanMbus10Value01		OBJECT-TYPE
			SYNTAX	INTEGER
			MAX-ACCESS	read-only
			STATUS	current
			::= { hmWanMbus10 9 }

hmWanMbus10VIF02		OBJECT-TYPE
			SYNTAX	INTEGER
			MAX-ACCESS	read-only
			STATUS	current
			::= { hmWanMbus10 10 }

hmWanMbus10Value02		OBJECT-TYPE
			SYNTAX	INTEGER
			MAX-ACCESS	read-only
			STATUS	current
			::= { hmWanMbus10 11 }

hmWanMbus10VIF03		OBJECT-TYPE
			SYNTAX	INTEGER
			MAX-ACCESS	read-only
			STATUS	current
			::= { hmWanMbus10 12 }

hmWanMbus10Value03		OBJECT-TYPE
			SYNTAX	INTEGER
			MAX-ACCESS	read-only
			STATUS	current
			::= { hmWanMbus10 13 }

hmWanMbus10VIF04		OBJECT-TYPE
			SYNTAX	INTEGER
			MAX-ACCESS	read-only
			STATUS	current
			::= { hmWanMbus10 14 }

hmWanMbus10Value04		OBJECT-TYPE
			SYNTAX	INTEGER
			MAX-ACCESS	read-only
			STATUS	current
			::= { hmWanMbus10 15 }

hmWanMbus10VIF05		OBJECT-TYPE
			SYNTAX	INTEGER
			MAX-ACCESS	read-only
			STATUS	current
			::= { hmWanMbus10 16 }

hmWanMbus10Value05		OBJECT-TYPE
			SYNTAX	INTEGER
			MAX-ACCESS	read-only
			STATUS	current
			::= { hmWanMbus10 17 }

hmWanMbus10VIF06		OBJECT-TYPE
			SYNTAX	INTEGER
			MAX-ACCESS	read-only
			STATUS	current
			::= { hmWanMbus10 18 }

hmWanMbus10Value06		OBJECT-TYPE
			SYNTAX	INTEGER
			MAX-ACCESS	read-only
			STATUS	current
			::= { hmWanMbus10 19 }

hmWanMbus10VIF07		OBJECT-TYPE
			SYNTAX	INTEGER
			MAX-ACCESS	read-only
			STATUS	current
			::= { hmWanMbus10 20 }

hmWanMbus10Value07		OBJECT-TYPE
			SYNTAX	INTEGER
			MAX-ACCESS	read-only
			STATUS	current
			::= { hmWanMbus10 21 }

hmWanMbus10VIF08		OBJECT-TYPE
			SYNTAX	INTEGER
			MAX-ACCESS	read-only
			STATUS	current
			::= { hmWanMbus10 22 }

hmWanMbus10Value08		OBJECT-TYPE
			SYNTAX	INTEGER
			MAX-ACCESS	read-only
			STATUS	current
			::= { hmWanMbus10 23 }

hmWanMbus10VIF09		OBJECT-TYPE
			SYNTAX	INTEGER
			MAX-ACCESS	read-only
			STATUS	current
			::= { hmWanMbus10 24 }

hmWanMbus10Value09		OBJECT-TYPE
			SYNTAX	INTEGER
			MAX-ACCESS	read-only
			STATUS	current
			::= { hmWanMbus10 25 }

hmWanMbus10VIF0A		OBJECT-TYPE
			SYNTAX	INTEGER
			MAX-ACCESS	read-only
			STATUS	current
			::= { hmWanMbus10 26 }

hmWanMbus10Value0A		OBJECT-TYPE
			SYNTAX	INTEGER
			MAX-ACCESS	read-only
			STATUS	current
			::= { hmWanMbus10 27 }

hmWanMbus10VIF0B		OBJECT-TYPE
			SYNTAX	INTEGER
			MAX-ACCESS	read-only
			STATUS	current
			::= { hmWanMbus10 28 }

hmWanMbus10Value0B		OBJECT-TYPE
			SYNTAX	INTEGER
			MAX-ACCESS	read-only
			STATUS	current
			::= { hmWanMbus10 29 }

hmWanMbus10VIF0C		OBJECT-TYPE
			SYNTAX	INTEGER
			MAX-ACCESS	read-only
			STATUS	current
			::= { hmWanMbus10 30 }

hmWanMbus10Value0C		OBJECT-TYPE
			SYNTAX	INTEGER
			MAX-ACCESS	read-only
			STATUS	current
			::= { hmWanMbus10 31 }

hmWanMbus10VIF0D		OBJECT-TYPE
			SYNTAX	INTEGER
			MAX-ACCESS	read-only
			STATUS	current
			::= { hmWanMbus10 32 }

hmWanMbus10Value0D		OBJECT-TYPE
			SYNTAX	INTEGER
			MAX-ACCESS	read-only
			STATUS	current
			::= { hmWanMbus10 33 }

hmWanMbus10VIF0E		OBJECT-TYPE
			SYNTAX	INTEGER
			MAX-ACCESS	read-only
			STATUS	current
			::= { hmWanMbus10 34 }

hmWanMbus10Value0E		OBJECT-TYPE
			SYNTAX	INTEGER
			MAX-ACCESS	read-only
			STATUS	current
			::= { hmWanMbus10 35 }

hmWanMbus10VIF0F		OBJECT-TYPE
			SYNTAX	INTEGER
			MAX-ACCESS	read-only
			STATUS	current
			::= { hmWanMbus10 36 }

hmWanMbus10Value0F		OBJECT-TYPE
			SYNTAX	INTEGER
			MAX-ACCESS	read-only
			STATUS	current
			::= { hmWanMbus10 37 }

hmWanMbus10VIF10		OBJECT-TYPE
			SYNTAX	INTEGER
			MAX-ACCESS	read-only
			STATUS	current
			::= { hmWanMbus10 38 }

hmWanMbus10Value10		OBJECT-TYPE
			SYNTAX	INTEGER
			MAX-ACCESS	read-only
			STATUS	current
			::= { hmWanMbus10 39 }

hmWanMbus10VIF11		OBJECT-TYPE
			SYNTAX	INTEGER
			MAX-ACCESS	read-only
			STATUS	current
			::= { hmWanMbus10 40 }

hmWanMbus10Value11		OBJECT-TYPE
			SYNTAX	INTEGER
			MAX-ACCESS	read-only
			STATUS	current
			::= { hmWanMbus10 41 }

hmWanMbus10VIF12		OBJECT-TYPE
			SYNTAX	INTEGER
			MAX-ACCESS	read-only
			STATUS	current
			::= { hmWanMbus10 42 }

hmWanMbus10Value12		OBJECT-TYPE
			SYNTAX	INTEGER
			MAX-ACCESS	read-only
			STATUS	current
			::= { hmWanMbus10 43 }

hmWanMbus10VIF13		OBJECT-TYPE
			SYNTAX	INTEGER
			MAX-ACCESS	read-only
			STATUS	current
			::= { hmWanMbus10 44 }

hmWanMbus10Value13		OBJECT-TYPE
			SYNTAX	INTEGER
			MAX-ACCESS	read-only
			STATUS	current
			::= { hmWanMbus10 45 }

hmWanMbus10VIF14		OBJECT-TYPE
			SYNTAX	INTEGER
			MAX-ACCESS	read-only
			STATUS	current
			::= { hmWanMbus10 46 }

hmWanMbus10Value14		OBJECT-TYPE
			SYNTAX	INTEGER
			MAX-ACCESS	read-only
			STATUS	current
			::= { hmWanMbus10 47 }

hmWanMbus10VIF15		OBJECT-TYPE
			SYNTAX	INTEGER
			MAX-ACCESS	read-only
			STATUS	current
			::= { hmWanMbus10 48 }

hmWanMbus10Value15		OBJECT-TYPE
			SYNTAX	INTEGER
			MAX-ACCESS	read-only
			STATUS	current
			::= { hmWanMbus10 49 }

hmWanMbus10VIF16		OBJECT-TYPE
			SYNTAX	INTEGER
			MAX-ACCESS	read-only
			STATUS	current
			::= { hmWanMbus10 50 }

hmWanMbus10Value16		OBJECT-TYPE
			SYNTAX	INTEGER
			MAX-ACCESS	read-only
			STATUS	current
			::= { hmWanMbus10 51 }

hmWanMbus10VIF17		OBJECT-TYPE
			SYNTAX	INTEGER
			MAX-ACCESS	read-only
			STATUS	current
			::= { hmWanMbus10 52 }

hmWanMbus10Value17		OBJECT-TYPE
			SYNTAX	INTEGER
			MAX-ACCESS	read-only
			STATUS	current
			::= { hmWanMbus10 53 }

hmWanMbus10VIF18		OBJECT-TYPE
			SYNTAX	INTEGER
			MAX-ACCESS	read-only
			STATUS	current
			::= { hmWanMbus10 54 }

hmWanMbus10Value18		OBJECT-TYPE
			SYNTAX	INTEGER
			MAX-ACCESS	read-only
			STATUS	current
			::= { hmWanMbus10 55 }

hmWanMbus10VIF19		OBJECT-TYPE
			SYNTAX	INTEGER
			MAX-ACCESS	read-only
			STATUS	current
			::= { hmWanMbus10 56 }

hmWanMbus10Value19		OBJECT-TYPE
			SYNTAX	INTEGER
			MAX-ACCESS	read-only
			STATUS	current
			::= { hmWanMbus10 57 }

hmWanMbus10VIF1A		OBJECT-TYPE
			SYNTAX	INTEGER
			MAX-ACCESS	read-only
			STATUS	current
			::= { hmWanMbus10 58 }

hmWanMbus10Value1A		OBJECT-TYPE
			SYNTAX	INTEGER
			MAX-ACCESS	read-only
			STATUS	current
			::= { hmWanMbus10 59 }

hmWanMbus10VIF1B		OBJECT-TYPE
			SYNTAX	INTEGER
			MAX-ACCESS	read-only
			STATUS	current
			::= { hmWanMbus10 60 }

hmWanMbus10Value1B		OBJECT-TYPE
			SYNTAX	INTEGER
			MAX-ACCESS	read-only
			STATUS	current
			::= { hmWanMbus10 61 }

hmWanMbus10VIF1C		OBJECT-TYPE
			SYNTAX	INTEGER
			MAX-ACCESS	read-only
			STATUS	current
			::= { hmWanMbus10 62 }

hmWanMbus10Value1C		OBJECT-TYPE
			SYNTAX	INTEGER
			MAX-ACCESS	read-only
			STATUS	current
			::= { hmWanMbus10 63 }

hmWanMbus10VIF1D		OBJECT-TYPE
			SYNTAX	INTEGER
			MAX-ACCESS	read-only
			STATUS	current
			::= { hmWanMbus10 64 }

hmWanMbus10Value1D		OBJECT-TYPE
			SYNTAX	INTEGER
			MAX-ACCESS	read-only
			STATUS	current
			::= { hmWanMbus10 65 }

hmWanMbus10VIF1E		OBJECT-TYPE
			SYNTAX	INTEGER
			MAX-ACCESS	read-only
			STATUS	current
			::= { hmWanMbus10 66 }

hmWanMbus10Value1E		OBJECT-TYPE
			SYNTAX	INTEGER
			MAX-ACCESS	read-only
			STATUS	current
			::= { hmWanMbus10 67 }

hmWanMbus10VIF1F		OBJECT-TYPE
			SYNTAX	INTEGER
			MAX-ACCESS	read-only
			STATUS	current
			::= { hmWanMbus10 68 }

hmWanMbus10Value1F		OBJECT-TYPE
			SYNTAX	INTEGER
			MAX-ACCESS	read-only
			STATUS	current
			::= { hmWanMbus10 69 }

hmWanMbus10VIF20		OBJECT-TYPE
			SYNTAX	INTEGER
			MAX-ACCESS	read-only
			STATUS	current
			::= { hmWanMbus10 70 }

hmWanMbus10Value20		OBJECT-TYPE
			SYNTAX	INTEGER
			MAX-ACCESS	read-only
			STATUS	current
			::= { hmWanMbus10 71 }

hmWanMbus10VIF21		OBJECT-TYPE
			SYNTAX	INTEGER
			MAX-ACCESS	read-only
			STATUS	current
			::= { hmWanMbus10 72 }

hmWanMbus10Value21		OBJECT-TYPE
			SYNTAX	INTEGER
			MAX-ACCESS	read-only
			STATUS	current
			::= { hmWanMbus10 73 }

hmWanMbus10VIF22		OBJECT-TYPE
			SYNTAX	INTEGER
			MAX-ACCESS	read-only
			STATUS	current
			::= { hmWanMbus10 74 }

hmWanMbus10Value22		OBJECT-TYPE
			SYNTAX	INTEGER
			MAX-ACCESS	read-only
			STATUS	current
			::= { hmWanMbus10 75 }

hmWanMbus10VIF23		OBJECT-TYPE
			SYNTAX	INTEGER
			MAX-ACCESS	read-only
			STATUS	current
			::= { hmWanMbus10 76 }

hmWanMbus10Value23		OBJECT-TYPE
			SYNTAX	INTEGER
			MAX-ACCESS	read-only
			STATUS	current
			::= { hmWanMbus10 77 }

hmWanMbus10VIF24		OBJECT-TYPE
			SYNTAX	INTEGER
			MAX-ACCESS	read-only
			STATUS	current
			::= { hmWanMbus10 78 }

hmWanMbus10Value24		OBJECT-TYPE
			SYNTAX	INTEGER
			MAX-ACCESS	read-only
			STATUS	current
			::= { hmWanMbus10 79 }

hmWanMbus10VIF25		OBJECT-TYPE
			SYNTAX	INTEGER
			MAX-ACCESS	read-only
			STATUS	current
			::= { hmWanMbus10 80 }

hmWanMbus10Value25		OBJECT-TYPE
			SYNTAX	INTEGER
			MAX-ACCESS	read-only
			STATUS	current
			::= { hmWanMbus10 81 }

hmWanMbus10VIF26		OBJECT-TYPE
			SYNTAX	INTEGER
			MAX-ACCESS	read-only
			STATUS	current
			::= { hmWanMbus10 82 }

hmWanMbus10Value26		OBJECT-TYPE
			SYNTAX	INTEGER
			MAX-ACCESS	read-only
			STATUS	current
			::= { hmWanMbus10 83 }

hmWanMbus10VIF27		OBJECT-TYPE
			SYNTAX	INTEGER
			MAX-ACCESS	read-only
			STATUS	current
			::= { hmWanMbus10 84 }

hmWanMbus10Value27		OBJECT-TYPE
			SYNTAX	INTEGER
			MAX-ACCESS	read-only
			STATUS	current
			::= { hmWanMbus10 85 }

hmWanMbus10VIF28		OBJECT-TYPE
			SYNTAX	INTEGER
			MAX-ACCESS	read-only
			STATUS	current
			::= { hmWanMbus10 86 }

hmWanMbus10Value28		OBJECT-TYPE
			SYNTAX	INTEGER
			MAX-ACCESS	read-only
			STATUS	current
			::= { hmWanMbus10 87 }

hmWanMbus10VIF29		OBJECT-TYPE
			SYNTAX	INTEGER
			MAX-ACCESS	read-only
			STATUS	current
			::= { hmWanMbus10 88 }

hmWanMbus10Value29		OBJECT-TYPE
			SYNTAX	INTEGER
			MAX-ACCESS	read-only
			STATUS	current
			::= { hmWanMbus10 89 }

hmWanMbus10VIF2A		OBJECT-TYPE
			SYNTAX	INTEGER
			MAX-ACCESS	read-only
			STATUS	current
			::= { hmWanMbus10 90 }

hmWanMbus10Value2A		OBJECT-TYPE
			SYNTAX	INTEGER
			MAX-ACCESS	read-only
			STATUS	current
			::= { hmWanMbus10 91 }

hmWanMbus10VIF2B		OBJECT-TYPE
			SYNTAX	INTEGER
			MAX-ACCESS	read-only
			STATUS	current
			::= { hmWanMbus10 92 }

hmWanMbus10Value2B		OBJECT-TYPE
			SYNTAX	INTEGER
			MAX-ACCESS	read-only
			STATUS	current
			::= { hmWanMbus10 93 }

hmWanMbus10VIF2C		OBJECT-TYPE
			SYNTAX	INTEGER
			MAX-ACCESS	read-only
			STATUS	current
			::= { hmWanMbus10 94 }

hmWanMbus10Value2C		OBJECT-TYPE
			SYNTAX	INTEGER
			MAX-ACCESS	read-only
			STATUS	current
			::= { hmWanMbus10 95 }

hmWanMbus10VIF2D		OBJECT-TYPE
			SYNTAX	INTEGER
			MAX-ACCESS	read-only
			STATUS	current
			::= { hmWanMbus10 96 }

hmWanMbus10Value2D		OBJECT-TYPE
			SYNTAX	INTEGER
			MAX-ACCESS	read-only
			STATUS	current
			::= { hmWanMbus10 97 }

hmWanMbus10VIF2E		OBJECT-TYPE
			SYNTAX	INTEGER
			MAX-ACCESS	read-only
			STATUS	current
			::= { hmWanMbus10 98 }

hmWanMbus10Value2E		OBJECT-TYPE
			SYNTAX	INTEGER
			MAX-ACCESS	read-only
			STATUS	current
			::= { hmWanMbus10 99 }

hmWanMbus10VIF2F		OBJECT-TYPE
			SYNTAX	INTEGER
			MAX-ACCESS	read-only
			STATUS	current
			::= { hmWanMbus10 100 }

hmWanMbus10Value2F		OBJECT-TYPE
			SYNTAX	INTEGER
			MAX-ACCESS	read-only
			STATUS	current
			::= { hmWanMbus10 101 }

hmWanMbus11			OBJECT IDENTIFIER ::= { hmWanMbus 17 }

hmWanMbus11IdNumber		OBJECT-TYPE
			SYNTAX	Gauge32
			MAX-ACCESS	read-only
			STATUS	current
			::= { hmWanMbus11 1 }

hmWanMbus11Manufacturer	OBJECT-TYPE
			SYNTAX	Gauge32
			MAX-ACCESS	read-only
			STATUS	current
			::= { hmWanMbus11 2 }

hmWanMbus11Version		OBJECT-TYPE
			SYNTAX	Gauge32
			MAX-ACCESS	read-only
			STATUS	current
			::= { hmWanMbus11 3 }

hmWanMbus11Medium		OBJECT-TYPE
			SYNTAX	Gauge32
			MAX-ACCESS	read-only
			STATUS	current
			::= { hmWanMbus11 4 }

hmWanMbus11Status		OBJECT-TYPE
			SYNTAX	Gauge32
			MAX-ACCESS	read-only
			STATUS	current
			::= { hmWanMbus11 5 }

hmWanMbus11VIF00		OBJECT-TYPE
			SYNTAX	INTEGER
			MAX-ACCESS	read-only
			STATUS	current
			::= { hmWanMbus11 6 }

hmWanMbus11Value00		OBJECT-TYPE
			SYNTAX	INTEGER
			MAX-ACCESS	read-only
			STATUS	current
			::= { hmWanMbus11 7 }

hmWanMbus11VIF01		OBJECT-TYPE
			SYNTAX	INTEGER
			MAX-ACCESS	read-only
			STATUS	current
			::= { hmWanMbus11 8 }

hmWanMbus11Value01		OBJECT-TYPE
			SYNTAX	INTEGER
			MAX-ACCESS	read-only
			STATUS	current
			::= { hmWanMbus11 9 }

hmWanMbus11VIF02		OBJECT-TYPE
			SYNTAX	INTEGER
			MAX-ACCESS	read-only
			STATUS	current
			::= { hmWanMbus11 10 }

hmWanMbus11Value02		OBJECT-TYPE
			SYNTAX	INTEGER
			MAX-ACCESS	read-only
			STATUS	current
			::= { hmWanMbus11 11 }

hmWanMbus11VIF03		OBJECT-TYPE
			SYNTAX	INTEGER
			MAX-ACCESS	read-only
			STATUS	current
			::= { hmWanMbus11 12 }

hmWanMbus11Value03		OBJECT-TYPE
			SYNTAX	INTEGER
			MAX-ACCESS	read-only
			STATUS	current
			::= { hmWanMbus11 13 }

hmWanMbus11VIF04		OBJECT-TYPE
			SYNTAX	INTEGER
			MAX-ACCESS	read-only
			STATUS	current
			::= { hmWanMbus11 14 }

hmWanMbus11Value04		OBJECT-TYPE
			SYNTAX	INTEGER
			MAX-ACCESS	read-only
			STATUS	current
			::= { hmWanMbus11 15 }

hmWanMbus11VIF05		OBJECT-TYPE
			SYNTAX	INTEGER
			MAX-ACCESS	read-only
			STATUS	current
			::= { hmWanMbus11 16 }

hmWanMbus11Value05		OBJECT-TYPE
			SYNTAX	INTEGER
			MAX-ACCESS	read-only
			STATUS	current
			::= { hmWanMbus11 17 }

hmWanMbus11VIF06		OBJECT-TYPE
			SYNTAX	INTEGER
			MAX-ACCESS	read-only
			STATUS	current
			::= { hmWanMbus11 18 }

hmWanMbus11Value06		OBJECT-TYPE
			SYNTAX	INTEGER
			MAX-ACCESS	read-only
			STATUS	current
			::= { hmWanMbus11 19 }

hmWanMbus11VIF07		OBJECT-TYPE
			SYNTAX	INTEGER
			MAX-ACCESS	read-only
			STATUS	current
			::= { hmWanMbus11 20 }

hmWanMbus11Value07		OBJECT-TYPE
			SYNTAX	INTEGER
			MAX-ACCESS	read-only
			STATUS	current
			::= { hmWanMbus11 21 }

hmWanMbus11VIF08		OBJECT-TYPE
			SYNTAX	INTEGER
			MAX-ACCESS	read-only
			STATUS	current
			::= { hmWanMbus11 22 }

hmWanMbus11Value08		OBJECT-TYPE
			SYNTAX	INTEGER
			MAX-ACCESS	read-only
			STATUS	current
			::= { hmWanMbus11 23 }

hmWanMbus11VIF09		OBJECT-TYPE
			SYNTAX	INTEGER
			MAX-ACCESS	read-only
			STATUS	current
			::= { hmWanMbus11 24 }

hmWanMbus11Value09		OBJECT-TYPE
			SYNTAX	INTEGER
			MAX-ACCESS	read-only
			STATUS	current
			::= { hmWanMbus11 25 }

hmWanMbus11VIF0A		OBJECT-TYPE
			SYNTAX	INTEGER
			MAX-ACCESS	read-only
			STATUS	current
			::= { hmWanMbus11 26 }

hmWanMbus11Value0A		OBJECT-TYPE
			SYNTAX	INTEGER
			MAX-ACCESS	read-only
			STATUS	current
			::= { hmWanMbus11 27 }

hmWanMbus11VIF0B		OBJECT-TYPE
			SYNTAX	INTEGER
			MAX-ACCESS	read-only
			STATUS	current
			::= { hmWanMbus11 28 }

hmWanMbus11Value0B		OBJECT-TYPE
			SYNTAX	INTEGER
			MAX-ACCESS	read-only
			STATUS	current
			::= { hmWanMbus11 29 }

hmWanMbus11VIF0C		OBJECT-TYPE
			SYNTAX	INTEGER
			MAX-ACCESS	read-only
			STATUS	current
			::= { hmWanMbus11 30 }

hmWanMbus11Value0C		OBJECT-TYPE
			SYNTAX	INTEGER
			MAX-ACCESS	read-only
			STATUS	current
			::= { hmWanMbus11 31 }

hmWanMbus11VIF0D		OBJECT-TYPE
			SYNTAX	INTEGER
			MAX-ACCESS	read-only
			STATUS	current
			::= { hmWanMbus11 32 }

hmWanMbus11Value0D		OBJECT-TYPE
			SYNTAX	INTEGER
			MAX-ACCESS	read-only
			STATUS	current
			::= { hmWanMbus11 33 }

hmWanMbus11VIF0E		OBJECT-TYPE
			SYNTAX	INTEGER
			MAX-ACCESS	read-only
			STATUS	current
			::= { hmWanMbus11 34 }

hmWanMbus11Value0E		OBJECT-TYPE
			SYNTAX	INTEGER
			MAX-ACCESS	read-only
			STATUS	current
			::= { hmWanMbus11 35 }

hmWanMbus11VIF0F		OBJECT-TYPE
			SYNTAX	INTEGER
			MAX-ACCESS	read-only
			STATUS	current
			::= { hmWanMbus11 36 }

hmWanMbus11Value0F		OBJECT-TYPE
			SYNTAX	INTEGER
			MAX-ACCESS	read-only
			STATUS	current
			::= { hmWanMbus11 37 }

hmWanMbus11VIF10		OBJECT-TYPE
			SYNTAX	INTEGER
			MAX-ACCESS	read-only
			STATUS	current
			::= { hmWanMbus11 38 }

hmWanMbus11Value10		OBJECT-TYPE
			SYNTAX	INTEGER
			MAX-ACCESS	read-only
			STATUS	current
			::= { hmWanMbus11 39 }

hmWanMbus11VIF11		OBJECT-TYPE
			SYNTAX	INTEGER
			MAX-ACCESS	read-only
			STATUS	current
			::= { hmWanMbus11 40 }

hmWanMbus11Value11		OBJECT-TYPE
			SYNTAX	INTEGER
			MAX-ACCESS	read-only
			STATUS	current
			::= { hmWanMbus11 41 }

hmWanMbus11VIF12		OBJECT-TYPE
			SYNTAX	INTEGER
			MAX-ACCESS	read-only
			STATUS	current
			::= { hmWanMbus11 42 }

hmWanMbus11Value12		OBJECT-TYPE
			SYNTAX	INTEGER
			MAX-ACCESS	read-only
			STATUS	current
			::= { hmWanMbus11 43 }

hmWanMbus11VIF13		OBJECT-TYPE
			SYNTAX	INTEGER
			MAX-ACCESS	read-only
			STATUS	current
			::= { hmWanMbus11 44 }

hmWanMbus11Value13		OBJECT-TYPE
			SYNTAX	INTEGER
			MAX-ACCESS	read-only
			STATUS	current
			::= { hmWanMbus11 45 }

hmWanMbus11VIF14		OBJECT-TYPE
			SYNTAX	INTEGER
			MAX-ACCESS	read-only
			STATUS	current
			::= { hmWanMbus11 46 }

hmWanMbus11Value14		OBJECT-TYPE
			SYNTAX	INTEGER
			MAX-ACCESS	read-only
			STATUS	current
			::= { hmWanMbus11 47 }

hmWanMbus11VIF15		OBJECT-TYPE
			SYNTAX	INTEGER
			MAX-ACCESS	read-only
			STATUS	current
			::= { hmWanMbus11 48 }

hmWanMbus11Value15		OBJECT-TYPE
			SYNTAX	INTEGER
			MAX-ACCESS	read-only
			STATUS	current
			::= { hmWanMbus11 49 }

hmWanMbus11VIF16		OBJECT-TYPE
			SYNTAX	INTEGER
			MAX-ACCESS	read-only
			STATUS	current
			::= { hmWanMbus11 50 }

hmWanMbus11Value16		OBJECT-TYPE
			SYNTAX	INTEGER
			MAX-ACCESS	read-only
			STATUS	current
			::= { hmWanMbus11 51 }

hmWanMbus11VIF17		OBJECT-TYPE
			SYNTAX	INTEGER
			MAX-ACCESS	read-only
			STATUS	current
			::= { hmWanMbus11 52 }

hmWanMbus11Value17		OBJECT-TYPE
			SYNTAX	INTEGER
			MAX-ACCESS	read-only
			STATUS	current
			::= { hmWanMbus11 53 }

hmWanMbus11VIF18		OBJECT-TYPE
			SYNTAX	INTEGER
			MAX-ACCESS	read-only
			STATUS	current
			::= { hmWanMbus11 54 }

hmWanMbus11Value18		OBJECT-TYPE
			SYNTAX	INTEGER
			MAX-ACCESS	read-only
			STATUS	current
			::= { hmWanMbus11 55 }

hmWanMbus11VIF19		OBJECT-TYPE
			SYNTAX	INTEGER
			MAX-ACCESS	read-only
			STATUS	current
			::= { hmWanMbus11 56 }

hmWanMbus11Value19		OBJECT-TYPE
			SYNTAX	INTEGER
			MAX-ACCESS	read-only
			STATUS	current
			::= { hmWanMbus11 57 }

hmWanMbus11VIF1A		OBJECT-TYPE
			SYNTAX	INTEGER
			MAX-ACCESS	read-only
			STATUS	current
			::= { hmWanMbus11 58 }

hmWanMbus11Value1A		OBJECT-TYPE
			SYNTAX	INTEGER
			MAX-ACCESS	read-only
			STATUS	current
			::= { hmWanMbus11 59 }

hmWanMbus11VIF1B		OBJECT-TYPE
			SYNTAX	INTEGER
			MAX-ACCESS	read-only
			STATUS	current
			::= { hmWanMbus11 60 }

hmWanMbus11Value1B		OBJECT-TYPE
			SYNTAX	INTEGER
			MAX-ACCESS	read-only
			STATUS	current
			::= { hmWanMbus11 61 }

hmWanMbus11VIF1C		OBJECT-TYPE
			SYNTAX	INTEGER
			MAX-ACCESS	read-only
			STATUS	current
			::= { hmWanMbus11 62 }

hmWanMbus11Value1C		OBJECT-TYPE
			SYNTAX	INTEGER
			MAX-ACCESS	read-only
			STATUS	current
			::= { hmWanMbus11 63 }

hmWanMbus11VIF1D		OBJECT-TYPE
			SYNTAX	INTEGER
			MAX-ACCESS	read-only
			STATUS	current
			::= { hmWanMbus11 64 }

hmWanMbus11Value1D		OBJECT-TYPE
			SYNTAX	INTEGER
			MAX-ACCESS	read-only
			STATUS	current
			::= { hmWanMbus11 65 }

hmWanMbus11VIF1E		OBJECT-TYPE
			SYNTAX	INTEGER
			MAX-ACCESS	read-only
			STATUS	current
			::= { hmWanMbus11 66 }

hmWanMbus11Value1E		OBJECT-TYPE
			SYNTAX	INTEGER
			MAX-ACCESS	read-only
			STATUS	current
			::= { hmWanMbus11 67 }

hmWanMbus11VIF1F		OBJECT-TYPE
			SYNTAX	INTEGER
			MAX-ACCESS	read-only
			STATUS	current
			::= { hmWanMbus11 68 }

hmWanMbus11Value1F		OBJECT-TYPE
			SYNTAX	INTEGER
			MAX-ACCESS	read-only
			STATUS	current
			::= { hmWanMbus11 69 }

hmWanMbus11VIF20		OBJECT-TYPE
			SYNTAX	INTEGER
			MAX-ACCESS	read-only
			STATUS	current
			::= { hmWanMbus11 70 }

hmWanMbus11Value20		OBJECT-TYPE
			SYNTAX	INTEGER
			MAX-ACCESS	read-only
			STATUS	current
			::= { hmWanMbus11 71 }

hmWanMbus11VIF21		OBJECT-TYPE
			SYNTAX	INTEGER
			MAX-ACCESS	read-only
			STATUS	current
			::= { hmWanMbus11 72 }

hmWanMbus11Value21		OBJECT-TYPE
			SYNTAX	INTEGER
			MAX-ACCESS	read-only
			STATUS	current
			::= { hmWanMbus11 73 }

hmWanMbus11VIF22		OBJECT-TYPE
			SYNTAX	INTEGER
			MAX-ACCESS	read-only
			STATUS	current
			::= { hmWanMbus11 74 }

hmWanMbus11Value22		OBJECT-TYPE
			SYNTAX	INTEGER
			MAX-ACCESS	read-only
			STATUS	current
			::= { hmWanMbus11 75 }

hmWanMbus11VIF23		OBJECT-TYPE
			SYNTAX	INTEGER
			MAX-ACCESS	read-only
			STATUS	current
			::= { hmWanMbus11 76 }

hmWanMbus11Value23		OBJECT-TYPE
			SYNTAX	INTEGER
			MAX-ACCESS	read-only
			STATUS	current
			::= { hmWanMbus11 77 }

hmWanMbus11VIF24		OBJECT-TYPE
			SYNTAX	INTEGER
			MAX-ACCESS	read-only
			STATUS	current
			::= { hmWanMbus11 78 }

hmWanMbus11Value24		OBJECT-TYPE
			SYNTAX	INTEGER
			MAX-ACCESS	read-only
			STATUS	current
			::= { hmWanMbus11 79 }

hmWanMbus11VIF25		OBJECT-TYPE
			SYNTAX	INTEGER
			MAX-ACCESS	read-only
			STATUS	current
			::= { hmWanMbus11 80 }

hmWanMbus11Value25		OBJECT-TYPE
			SYNTAX	INTEGER
			MAX-ACCESS	read-only
			STATUS	current
			::= { hmWanMbus11 81 }

hmWanMbus11VIF26		OBJECT-TYPE
			SYNTAX	INTEGER
			MAX-ACCESS	read-only
			STATUS	current
			::= { hmWanMbus11 82 }

hmWanMbus11Value26		OBJECT-TYPE
			SYNTAX	INTEGER
			MAX-ACCESS	read-only
			STATUS	current
			::= { hmWanMbus11 83 }

hmWanMbus11VIF27		OBJECT-TYPE
			SYNTAX	INTEGER
			MAX-ACCESS	read-only
			STATUS	current
			::= { hmWanMbus11 84 }

hmWanMbus11Value27		OBJECT-TYPE
			SYNTAX	INTEGER
			MAX-ACCESS	read-only
			STATUS	current
			::= { hmWanMbus11 85 }

hmWanMbus11VIF28		OBJECT-TYPE
			SYNTAX	INTEGER
			MAX-ACCESS	read-only
			STATUS	current
			::= { hmWanMbus11 86 }

hmWanMbus11Value28		OBJECT-TYPE
			SYNTAX	INTEGER
			MAX-ACCESS	read-only
			STATUS	current
			::= { hmWanMbus11 87 }

hmWanMbus11VIF29		OBJECT-TYPE
			SYNTAX	INTEGER
			MAX-ACCESS	read-only
			STATUS	current
			::= { hmWanMbus11 88 }

hmWanMbus11Value29		OBJECT-TYPE
			SYNTAX	INTEGER
			MAX-ACCESS	read-only
			STATUS	current
			::= { hmWanMbus11 89 }

hmWanMbus11VIF2A		OBJECT-TYPE
			SYNTAX	INTEGER
			MAX-ACCESS	read-only
			STATUS	current
			::= { hmWanMbus11 90 }

hmWanMbus11Value2A		OBJECT-TYPE
			SYNTAX	INTEGER
			MAX-ACCESS	read-only
			STATUS	current
			::= { hmWanMbus11 91 }

hmWanMbus11VIF2B		OBJECT-TYPE
			SYNTAX	INTEGER
			MAX-ACCESS	read-only
			STATUS	current
			::= { hmWanMbus11 92 }

hmWanMbus11Value2B		OBJECT-TYPE
			SYNTAX	INTEGER
			MAX-ACCESS	read-only
			STATUS	current
			::= { hmWanMbus11 93 }

hmWanMbus11VIF2C		OBJECT-TYPE
			SYNTAX	INTEGER
			MAX-ACCESS	read-only
			STATUS	current
			::= { hmWanMbus11 94 }

hmWanMbus11Value2C		OBJECT-TYPE
			SYNTAX	INTEGER
			MAX-ACCESS	read-only
			STATUS	current
			::= { hmWanMbus11 95 }

hmWanMbus11VIF2D		OBJECT-TYPE
			SYNTAX	INTEGER
			MAX-ACCESS	read-only
			STATUS	current
			::= { hmWanMbus11 96 }

hmWanMbus11Value2D		OBJECT-TYPE
			SYNTAX	INTEGER
			MAX-ACCESS	read-only
			STATUS	current
			::= { hmWanMbus11 97 }

hmWanMbus11VIF2E		OBJECT-TYPE
			SYNTAX	INTEGER
			MAX-ACCESS	read-only
			STATUS	current
			::= { hmWanMbus11 98 }

hmWanMbus11Value2E		OBJECT-TYPE
			SYNTAX	INTEGER
			MAX-ACCESS	read-only
			STATUS	current
			::= { hmWanMbus11 99 }

hmWanMbus11VIF2F		OBJECT-TYPE
			SYNTAX	INTEGER
			MAX-ACCESS	read-only
			STATUS	current
			::= { hmWanMbus11 100 }

hmWanMbus11Value2F		OBJECT-TYPE
			SYNTAX	INTEGER
			MAX-ACCESS	read-only
			STATUS	current
			::= { hmWanMbus11 101 }

hmWanMbus12			OBJECT IDENTIFIER ::= { hmWanMbus 18 }

hmWanMbus12IdNumber		OBJECT-TYPE
			SYNTAX	Gauge32
			MAX-ACCESS	read-only
			STATUS	current
			::= { hmWanMbus12 1 }

hmWanMbus12Manufacturer	OBJECT-TYPE
			SYNTAX	Gauge32
			MAX-ACCESS	read-only
			STATUS	current
			::= { hmWanMbus12 2 }

hmWanMbus12Version		OBJECT-TYPE
			SYNTAX	Gauge32
			MAX-ACCESS	read-only
			STATUS	current
			::= { hmWanMbus12 3 }

hmWanMbus12Medium		OBJECT-TYPE
			SYNTAX	Gauge32
			MAX-ACCESS	read-only
			STATUS	current
			::= { hmWanMbus12 4 }

hmWanMbus12Status		OBJECT-TYPE
			SYNTAX	Gauge32
			MAX-ACCESS	read-only
			STATUS	current
			::= { hmWanMbus12 5 }

hmWanMbus12VIF00		OBJECT-TYPE
			SYNTAX	INTEGER
			MAX-ACCESS	read-only
			STATUS	current
			::= { hmWanMbus12 6 }

hmWanMbus12Value00		OBJECT-TYPE
			SYNTAX	INTEGER
			MAX-ACCESS	read-only
			STATUS	current
			::= { hmWanMbus12 7 }

hmWanMbus12VIF01		OBJECT-TYPE
			SYNTAX	INTEGER
			MAX-ACCESS	read-only
			STATUS	current
			::= { hmWanMbus12 8 }

hmWanMbus12Value01		OBJECT-TYPE
			SYNTAX	INTEGER
			MAX-ACCESS	read-only
			STATUS	current
			::= { hmWanMbus12 9 }

hmWanMbus12VIF02		OBJECT-TYPE
			SYNTAX	INTEGER
			MAX-ACCESS	read-only
			STATUS	current
			::= { hmWanMbus12 10 }

hmWanMbus12Value02		OBJECT-TYPE
			SYNTAX	INTEGER
			MAX-ACCESS	read-only
			STATUS	current
			::= { hmWanMbus12 11 }

hmWanMbus12VIF03		OBJECT-TYPE
			SYNTAX	INTEGER
			MAX-ACCESS	read-only
			STATUS	current
			::= { hmWanMbus12 12 }

hmWanMbus12Value03		OBJECT-TYPE
			SYNTAX	INTEGER
			MAX-ACCESS	read-only
			STATUS	current
			::= { hmWanMbus12 13 }

hmWanMbus12VIF04		OBJECT-TYPE
			SYNTAX	INTEGER
			MAX-ACCESS	read-only
			STATUS	current
			::= { hmWanMbus12 14 }

hmWanMbus12Value04		OBJECT-TYPE
			SYNTAX	INTEGER
			MAX-ACCESS	read-only
			STATUS	current
			::= { hmWanMbus12 15 }

hmWanMbus12VIF05		OBJECT-TYPE
			SYNTAX	INTEGER
			MAX-ACCESS	read-only
			STATUS	current
			::= { hmWanMbus12 16 }

hmWanMbus12Value05		OBJECT-TYPE
			SYNTAX	INTEGER
			MAX-ACCESS	read-only
			STATUS	current
			::= { hmWanMbus12 17 }

hmWanMbus12VIF06		OBJECT-TYPE
			SYNTAX	INTEGER
			MAX-ACCESS	read-only
			STATUS	current
			::= { hmWanMbus12 18 }

hmWanMbus12Value06		OBJECT-TYPE
			SYNTAX	INTEGER
			MAX-ACCESS	read-only
			STATUS	current
			::= { hmWanMbus12 19 }

hmWanMbus12VIF07		OBJECT-TYPE
			SYNTAX	INTEGER
			MAX-ACCESS	read-only
			STATUS	current
			::= { hmWanMbus12 20 }

hmWanMbus12Value07		OBJECT-TYPE
			SYNTAX	INTEGER
			MAX-ACCESS	read-only
			STATUS	current
			::= { hmWanMbus12 21 }

hmWanMbus12VIF08		OBJECT-TYPE
			SYNTAX	INTEGER
			MAX-ACCESS	read-only
			STATUS	current
			::= { hmWanMbus12 22 }

hmWanMbus12Value08		OBJECT-TYPE
			SYNTAX	INTEGER
			MAX-ACCESS	read-only
			STATUS	current
			::= { hmWanMbus12 23 }

hmWanMbus12VIF09		OBJECT-TYPE
			SYNTAX	INTEGER
			MAX-ACCESS	read-only
			STATUS	current
			::= { hmWanMbus12 24 }

hmWanMbus12Value09		OBJECT-TYPE
			SYNTAX	INTEGER
			MAX-ACCESS	read-only
			STATUS	current
			::= { hmWanMbus12 25 }

hmWanMbus12VIF0A		OBJECT-TYPE
			SYNTAX	INTEGER
			MAX-ACCESS	read-only
			STATUS	current
			::= { hmWanMbus12 26 }

hmWanMbus12Value0A		OBJECT-TYPE
			SYNTAX	INTEGER
			MAX-ACCESS	read-only
			STATUS	current
			::= { hmWanMbus12 27 }

hmWanMbus12VIF0B		OBJECT-TYPE
			SYNTAX	INTEGER
			MAX-ACCESS	read-only
			STATUS	current
			::= { hmWanMbus12 28 }

hmWanMbus12Value0B		OBJECT-TYPE
			SYNTAX	INTEGER
			MAX-ACCESS	read-only
			STATUS	current
			::= { hmWanMbus12 29 }

hmWanMbus12VIF0C		OBJECT-TYPE
			SYNTAX	INTEGER
			MAX-ACCESS	read-only
			STATUS	current
			::= { hmWanMbus12 30 }

hmWanMbus12Value0C		OBJECT-TYPE
			SYNTAX	INTEGER
			MAX-ACCESS	read-only
			STATUS	current
			::= { hmWanMbus12 31 }

hmWanMbus12VIF0D		OBJECT-TYPE
			SYNTAX	INTEGER
			MAX-ACCESS	read-only
			STATUS	current
			::= { hmWanMbus12 32 }

hmWanMbus12Value0D		OBJECT-TYPE
			SYNTAX	INTEGER
			MAX-ACCESS	read-only
			STATUS	current
			::= { hmWanMbus12 33 }

hmWanMbus12VIF0E		OBJECT-TYPE
			SYNTAX	INTEGER
			MAX-ACCESS	read-only
			STATUS	current
			::= { hmWanMbus12 34 }

hmWanMbus12Value0E		OBJECT-TYPE
			SYNTAX	INTEGER
			MAX-ACCESS	read-only
			STATUS	current
			::= { hmWanMbus12 35 }

hmWanMbus12VIF0F		OBJECT-TYPE
			SYNTAX	INTEGER
			MAX-ACCESS	read-only
			STATUS	current
			::= { hmWanMbus12 36 }

hmWanMbus12Value0F		OBJECT-TYPE
			SYNTAX	INTEGER
			MAX-ACCESS	read-only
			STATUS	current
			::= { hmWanMbus12 37 }

hmWanMbus12VIF10		OBJECT-TYPE
			SYNTAX	INTEGER
			MAX-ACCESS	read-only
			STATUS	current
			::= { hmWanMbus12 38 }

hmWanMbus12Value10		OBJECT-TYPE
			SYNTAX	INTEGER
			MAX-ACCESS	read-only
			STATUS	current
			::= { hmWanMbus12 39 }

hmWanMbus12VIF11		OBJECT-TYPE
			SYNTAX	INTEGER
			MAX-ACCESS	read-only
			STATUS	current
			::= { hmWanMbus12 40 }

hmWanMbus12Value11		OBJECT-TYPE
			SYNTAX	INTEGER
			MAX-ACCESS	read-only
			STATUS	current
			::= { hmWanMbus12 41 }

hmWanMbus12VIF12		OBJECT-TYPE
			SYNTAX	INTEGER
			MAX-ACCESS	read-only
			STATUS	current
			::= { hmWanMbus12 42 }

hmWanMbus12Value12		OBJECT-TYPE
			SYNTAX	INTEGER
			MAX-ACCESS	read-only
			STATUS	current
			::= { hmWanMbus12 43 }

hmWanMbus12VIF13		OBJECT-TYPE
			SYNTAX	INTEGER
			MAX-ACCESS	read-only
			STATUS	current
			::= { hmWanMbus12 44 }

hmWanMbus12Value13		OBJECT-TYPE
			SYNTAX	INTEGER
			MAX-ACCESS	read-only
			STATUS	current
			::= { hmWanMbus12 45 }

hmWanMbus12VIF14		OBJECT-TYPE
			SYNTAX	INTEGER
			MAX-ACCESS	read-only
			STATUS	current
			::= { hmWanMbus12 46 }

hmWanMbus12Value14		OBJECT-TYPE
			SYNTAX	INTEGER
			MAX-ACCESS	read-only
			STATUS	current
			::= { hmWanMbus12 47 }

hmWanMbus12VIF15		OBJECT-TYPE
			SYNTAX	INTEGER
			MAX-ACCESS	read-only
			STATUS	current
			::= { hmWanMbus12 48 }

hmWanMbus12Value15		OBJECT-TYPE
			SYNTAX	INTEGER
			MAX-ACCESS	read-only
			STATUS	current
			::= { hmWanMbus12 49 }

hmWanMbus12VIF16		OBJECT-TYPE
			SYNTAX	INTEGER
			MAX-ACCESS	read-only
			STATUS	current
			::= { hmWanMbus12 50 }

hmWanMbus12Value16		OBJECT-TYPE
			SYNTAX	INTEGER
			MAX-ACCESS	read-only
			STATUS	current
			::= { hmWanMbus12 51 }

hmWanMbus12VIF17		OBJECT-TYPE
			SYNTAX	INTEGER
			MAX-ACCESS	read-only
			STATUS	current
			::= { hmWanMbus12 52 }

hmWanMbus12Value17		OBJECT-TYPE
			SYNTAX	INTEGER
			MAX-ACCESS	read-only
			STATUS	current
			::= { hmWanMbus12 53 }

hmWanMbus12VIF18		OBJECT-TYPE
			SYNTAX	INTEGER
			MAX-ACCESS	read-only
			STATUS	current
			::= { hmWanMbus12 54 }

hmWanMbus12Value18		OBJECT-TYPE
			SYNTAX	INTEGER
			MAX-ACCESS	read-only
			STATUS	current
			::= { hmWanMbus12 55 }

hmWanMbus12VIF19		OBJECT-TYPE
			SYNTAX	INTEGER
			MAX-ACCESS	read-only
			STATUS	current
			::= { hmWanMbus12 56 }

hmWanMbus12Value19		OBJECT-TYPE
			SYNTAX	INTEGER
			MAX-ACCESS	read-only
			STATUS	current
			::= { hmWanMbus12 57 }

hmWanMbus12VIF1A		OBJECT-TYPE
			SYNTAX	INTEGER
			MAX-ACCESS	read-only
			STATUS	current
			::= { hmWanMbus12 58 }

hmWanMbus12Value1A		OBJECT-TYPE
			SYNTAX	INTEGER
			MAX-ACCESS	read-only
			STATUS	current
			::= { hmWanMbus12 59 }

hmWanMbus12VIF1B		OBJECT-TYPE
			SYNTAX	INTEGER
			MAX-ACCESS	read-only
			STATUS	current
			::= { hmWanMbus12 60 }

hmWanMbus12Value1B		OBJECT-TYPE
			SYNTAX	INTEGER
			MAX-ACCESS	read-only
			STATUS	current
			::= { hmWanMbus12 61 }

hmWanMbus12VIF1C		OBJECT-TYPE
			SYNTAX	INTEGER
			MAX-ACCESS	read-only
			STATUS	current
			::= { hmWanMbus12 62 }

hmWanMbus12Value1C		OBJECT-TYPE
			SYNTAX	INTEGER
			MAX-ACCESS	read-only
			STATUS	current
			::= { hmWanMbus12 63 }

hmWanMbus12VIF1D		OBJECT-TYPE
			SYNTAX	INTEGER
			MAX-ACCESS	read-only
			STATUS	current
			::= { hmWanMbus12 64 }

hmWanMbus12Value1D		OBJECT-TYPE
			SYNTAX	INTEGER
			MAX-ACCESS	read-only
			STATUS	current
			::= { hmWanMbus12 65 }

hmWanMbus12VIF1E		OBJECT-TYPE
			SYNTAX	INTEGER
			MAX-ACCESS	read-only
			STATUS	current
			::= { hmWanMbus12 66 }

hmWanMbus12Value1E		OBJECT-TYPE
			SYNTAX	INTEGER
			MAX-ACCESS	read-only
			STATUS	current
			::= { hmWanMbus12 67 }

hmWanMbus12VIF1F		OBJECT-TYPE
			SYNTAX	INTEGER
			MAX-ACCESS	read-only
			STATUS	current
			::= { hmWanMbus12 68 }

hmWanMbus12Value1F		OBJECT-TYPE
			SYNTAX	INTEGER
			MAX-ACCESS	read-only
			STATUS	current
			::= { hmWanMbus12 69 }

hmWanMbus12VIF20		OBJECT-TYPE
			SYNTAX	INTEGER
			MAX-ACCESS	read-only
			STATUS	current
			::= { hmWanMbus12 70 }

hmWanMbus12Value20		OBJECT-TYPE
			SYNTAX	INTEGER
			MAX-ACCESS	read-only
			STATUS	current
			::= { hmWanMbus12 71 }

hmWanMbus12VIF21		OBJECT-TYPE
			SYNTAX	INTEGER
			MAX-ACCESS	read-only
			STATUS	current
			::= { hmWanMbus12 72 }

hmWanMbus12Value21		OBJECT-TYPE
			SYNTAX	INTEGER
			MAX-ACCESS	read-only
			STATUS	current
			::= { hmWanMbus12 73 }

hmWanMbus12VIF22		OBJECT-TYPE
			SYNTAX	INTEGER
			MAX-ACCESS	read-only
			STATUS	current
			::= { hmWanMbus12 74 }

hmWanMbus12Value22		OBJECT-TYPE
			SYNTAX	INTEGER
			MAX-ACCESS	read-only
			STATUS	current
			::= { hmWanMbus12 75 }

hmWanMbus12VIF23		OBJECT-TYPE
			SYNTAX	INTEGER
			MAX-ACCESS	read-only
			STATUS	current
			::= { hmWanMbus12 76 }

hmWanMbus12Value23		OBJECT-TYPE
			SYNTAX	INTEGER
			MAX-ACCESS	read-only
			STATUS	current
			::= { hmWanMbus12 77 }

hmWanMbus12VIF24		OBJECT-TYPE
			SYNTAX	INTEGER
			MAX-ACCESS	read-only
			STATUS	current
			::= { hmWanMbus12 78 }

hmWanMbus12Value24		OBJECT-TYPE
			SYNTAX	INTEGER
			MAX-ACCESS	read-only
			STATUS	current
			::= { hmWanMbus12 79 }

hmWanMbus12VIF25		OBJECT-TYPE
			SYNTAX	INTEGER
			MAX-ACCESS	read-only
			STATUS	current
			::= { hmWanMbus12 80 }

hmWanMbus12Value25		OBJECT-TYPE
			SYNTAX	INTEGER
			MAX-ACCESS	read-only
			STATUS	current
			::= { hmWanMbus12 81 }

hmWanMbus12VIF26		OBJECT-TYPE
			SYNTAX	INTEGER
			MAX-ACCESS	read-only
			STATUS	current
			::= { hmWanMbus12 82 }

hmWanMbus12Value26		OBJECT-TYPE
			SYNTAX	INTEGER
			MAX-ACCESS	read-only
			STATUS	current
			::= { hmWanMbus12 83 }

hmWanMbus12VIF27		OBJECT-TYPE
			SYNTAX	INTEGER
			MAX-ACCESS	read-only
			STATUS	current
			::= { hmWanMbus12 84 }

hmWanMbus12Value27		OBJECT-TYPE
			SYNTAX	INTEGER
			MAX-ACCESS	read-only
			STATUS	current
			::= { hmWanMbus12 85 }

hmWanMbus12VIF28		OBJECT-TYPE
			SYNTAX	INTEGER
			MAX-ACCESS	read-only
			STATUS	current
			::= { hmWanMbus12 86 }

hmWanMbus12Value28		OBJECT-TYPE
			SYNTAX	INTEGER
			MAX-ACCESS	read-only
			STATUS	current
			::= { hmWanMbus12 87 }

hmWanMbus12VIF29		OBJECT-TYPE
			SYNTAX	INTEGER
			MAX-ACCESS	read-only
			STATUS	current
			::= { hmWanMbus12 88 }

hmWanMbus12Value29		OBJECT-TYPE
			SYNTAX	INTEGER
			MAX-ACCESS	read-only
			STATUS	current
			::= { hmWanMbus12 89 }

hmWanMbus12VIF2A		OBJECT-TYPE
			SYNTAX	INTEGER
			MAX-ACCESS	read-only
			STATUS	current
			::= { hmWanMbus12 90 }

hmWanMbus12Value2A		OBJECT-TYPE
			SYNTAX	INTEGER
			MAX-ACCESS	read-only
			STATUS	current
			::= { hmWanMbus12 91 }

hmWanMbus12VIF2B		OBJECT-TYPE
			SYNTAX	INTEGER
			MAX-ACCESS	read-only
			STATUS	current
			::= { hmWanMbus12 92 }

hmWanMbus12Value2B		OBJECT-TYPE
			SYNTAX	INTEGER
			MAX-ACCESS	read-only
			STATUS	current
			::= { hmWanMbus12 93 }

hmWanMbus12VIF2C		OBJECT-TYPE
			SYNTAX	INTEGER
			MAX-ACCESS	read-only
			STATUS	current
			::= { hmWanMbus12 94 }

hmWanMbus12Value2C		OBJECT-TYPE
			SYNTAX	INTEGER
			MAX-ACCESS	read-only
			STATUS	current
			::= { hmWanMbus12 95 }

hmWanMbus12VIF2D		OBJECT-TYPE
			SYNTAX	INTEGER
			MAX-ACCESS	read-only
			STATUS	current
			::= { hmWanMbus12 96 }

hmWanMbus12Value2D		OBJECT-TYPE
			SYNTAX	INTEGER
			MAX-ACCESS	read-only
			STATUS	current
			::= { hmWanMbus12 97 }

hmWanMbus12VIF2E		OBJECT-TYPE
			SYNTAX	INTEGER
			MAX-ACCESS	read-only
			STATUS	current
			::= { hmWanMbus12 98 }

hmWanMbus12Value2E		OBJECT-TYPE
			SYNTAX	INTEGER
			MAX-ACCESS	read-only
			STATUS	current
			::= { hmWanMbus12 99 }

hmWanMbus12VIF2F		OBJECT-TYPE
			SYNTAX	INTEGER
			MAX-ACCESS	read-only
			STATUS	current
			::= { hmWanMbus12 100 }

hmWanMbus12Value2F		OBJECT-TYPE
			SYNTAX	INTEGER
			MAX-ACCESS	read-only
			STATUS	current
			::= { hmWanMbus12 101 }

hmWanMbus13			OBJECT IDENTIFIER ::= { hmWanMbus 19 }

hmWanMbus13IdNumber		OBJECT-TYPE
			SYNTAX	Gauge32
			MAX-ACCESS	read-only
			STATUS	current
			::= { hmWanMbus13 1 }

hmWanMbus13Manufacturer	OBJECT-TYPE
			SYNTAX	Gauge32
			MAX-ACCESS	read-only
			STATUS	current
			::= { hmWanMbus13 2 }

hmWanMbus13Version		OBJECT-TYPE
			SYNTAX	Gauge32
			MAX-ACCESS	read-only
			STATUS	current
			::= { hmWanMbus13 3 }

hmWanMbus13Medium		OBJECT-TYPE
			SYNTAX	Gauge32
			MAX-ACCESS	read-only
			STATUS	current
			::= { hmWanMbus13 4 }

hmWanMbus13Status		OBJECT-TYPE
			SYNTAX	Gauge32
			MAX-ACCESS	read-only
			STATUS	current
			::= { hmWanMbus13 5 }

hmWanMbus13VIF00		OBJECT-TYPE
			SYNTAX	INTEGER
			MAX-ACCESS	read-only
			STATUS	current
			::= { hmWanMbus13 6 }

hmWanMbus13Value00		OBJECT-TYPE
			SYNTAX	INTEGER
			MAX-ACCESS	read-only
			STATUS	current
			::= { hmWanMbus13 7 }

hmWanMbus13VIF01		OBJECT-TYPE
			SYNTAX	INTEGER
			MAX-ACCESS	read-only
			STATUS	current
			::= { hmWanMbus13 8 }

hmWanMbus13Value01		OBJECT-TYPE
			SYNTAX	INTEGER
			MAX-ACCESS	read-only
			STATUS	current
			::= { hmWanMbus13 9 }

hmWanMbus13VIF02		OBJECT-TYPE
			SYNTAX	INTEGER
			MAX-ACCESS	read-only
			STATUS	current
			::= { hmWanMbus13 10 }

hmWanMbus13Value02		OBJECT-TYPE
			SYNTAX	INTEGER
			MAX-ACCESS	read-only
			STATUS	current
			::= { hmWanMbus13 11 }

hmWanMbus13VIF03		OBJECT-TYPE
			SYNTAX	INTEGER
			MAX-ACCESS	read-only
			STATUS	current
			::= { hmWanMbus13 12 }

hmWanMbus13Value03		OBJECT-TYPE
			SYNTAX	INTEGER
			MAX-ACCESS	read-only
			STATUS	current
			::= { hmWanMbus13 13 }

hmWanMbus13VIF04		OBJECT-TYPE
			SYNTAX	INTEGER
			MAX-ACCESS	read-only
			STATUS	current
			::= { hmWanMbus13 14 }

hmWanMbus13Value04		OBJECT-TYPE
			SYNTAX	INTEGER
			MAX-ACCESS	read-only
			STATUS	current
			::= { hmWanMbus13 15 }

hmWanMbus13VIF05		OBJECT-TYPE
			SYNTAX	INTEGER
			MAX-ACCESS	read-only
			STATUS	current
			::= { hmWanMbus13 16 }

hmWanMbus13Value05		OBJECT-TYPE
			SYNTAX	INTEGER
			MAX-ACCESS	read-only
			STATUS	current
			::= { hmWanMbus13 17 }

hmWanMbus13VIF06		OBJECT-TYPE
			SYNTAX	INTEGER
			MAX-ACCESS	read-only
			STATUS	current
			::= { hmWanMbus13 18 }

hmWanMbus13Value06		OBJECT-TYPE
			SYNTAX	INTEGER
			MAX-ACCESS	read-only
			STATUS	current
			::= { hmWanMbus13 19 }

hmWanMbus13VIF07		OBJECT-TYPE
			SYNTAX	INTEGER
			MAX-ACCESS	read-only
			STATUS	current
			::= { hmWanMbus13 20 }

hmWanMbus13Value07		OBJECT-TYPE
			SYNTAX	INTEGER
			MAX-ACCESS	read-only
			STATUS	current
			::= { hmWanMbus13 21 }

hmWanMbus13VIF08		OBJECT-TYPE
			SYNTAX	INTEGER
			MAX-ACCESS	read-only
			STATUS	current
			::= { hmWanMbus13 22 }

hmWanMbus13Value08		OBJECT-TYPE
			SYNTAX	INTEGER
			MAX-ACCESS	read-only
			STATUS	current
			::= { hmWanMbus13 23 }

hmWanMbus13VIF09		OBJECT-TYPE
			SYNTAX	INTEGER
			MAX-ACCESS	read-only
			STATUS	current
			::= { hmWanMbus13 24 }

hmWanMbus13Value09		OBJECT-TYPE
			SYNTAX	INTEGER
			MAX-ACCESS	read-only
			STATUS	current
			::= { hmWanMbus13 25 }

hmWanMbus13VIF0A		OBJECT-TYPE
			SYNTAX	INTEGER
			MAX-ACCESS	read-only
			STATUS	current
			::= { hmWanMbus13 26 }

hmWanMbus13Value0A		OBJECT-TYPE
			SYNTAX	INTEGER
			MAX-ACCESS	read-only
			STATUS	current
			::= { hmWanMbus13 27 }

hmWanMbus13VIF0B		OBJECT-TYPE
			SYNTAX	INTEGER
			MAX-ACCESS	read-only
			STATUS	current
			::= { hmWanMbus13 28 }

hmWanMbus13Value0B		OBJECT-TYPE
			SYNTAX	INTEGER
			MAX-ACCESS	read-only
			STATUS	current
			::= { hmWanMbus13 29 }

hmWanMbus13VIF0C		OBJECT-TYPE
			SYNTAX	INTEGER
			MAX-ACCESS	read-only
			STATUS	current
			::= { hmWanMbus13 30 }

hmWanMbus13Value0C		OBJECT-TYPE
			SYNTAX	INTEGER
			MAX-ACCESS	read-only
			STATUS	current
			::= { hmWanMbus13 31 }

hmWanMbus13VIF0D		OBJECT-TYPE
			SYNTAX	INTEGER
			MAX-ACCESS	read-only
			STATUS	current
			::= { hmWanMbus13 32 }

hmWanMbus13Value0D		OBJECT-TYPE
			SYNTAX	INTEGER
			MAX-ACCESS	read-only
			STATUS	current
			::= { hmWanMbus13 33 }

hmWanMbus13VIF0E		OBJECT-TYPE
			SYNTAX	INTEGER
			MAX-ACCESS	read-only
			STATUS	current
			::= { hmWanMbus13 34 }

hmWanMbus13Value0E		OBJECT-TYPE
			SYNTAX	INTEGER
			MAX-ACCESS	read-only
			STATUS	current
			::= { hmWanMbus13 35 }

hmWanMbus13VIF0F		OBJECT-TYPE
			SYNTAX	INTEGER
			MAX-ACCESS	read-only
			STATUS	current
			::= { hmWanMbus13 36 }

hmWanMbus13Value0F		OBJECT-TYPE
			SYNTAX	INTEGER
			MAX-ACCESS	read-only
			STATUS	current
			::= { hmWanMbus13 37 }

hmWanMbus13VIF10		OBJECT-TYPE
			SYNTAX	INTEGER
			MAX-ACCESS	read-only
			STATUS	current
			::= { hmWanMbus13 38 }

hmWanMbus13Value10		OBJECT-TYPE
			SYNTAX	INTEGER
			MAX-ACCESS	read-only
			STATUS	current
			::= { hmWanMbus13 39 }

hmWanMbus13VIF11		OBJECT-TYPE
			SYNTAX	INTEGER
			MAX-ACCESS	read-only
			STATUS	current
			::= { hmWanMbus13 40 }

hmWanMbus13Value11		OBJECT-TYPE
			SYNTAX	INTEGER
			MAX-ACCESS	read-only
			STATUS	current
			::= { hmWanMbus13 41 }

hmWanMbus13VIF12		OBJECT-TYPE
			SYNTAX	INTEGER
			MAX-ACCESS	read-only
			STATUS	current
			::= { hmWanMbus13 42 }

hmWanMbus13Value12		OBJECT-TYPE
			SYNTAX	INTEGER
			MAX-ACCESS	read-only
			STATUS	current
			::= { hmWanMbus13 43 }

hmWanMbus13VIF13		OBJECT-TYPE
			SYNTAX	INTEGER
			MAX-ACCESS	read-only
			STATUS	current
			::= { hmWanMbus13 44 }

hmWanMbus13Value13		OBJECT-TYPE
			SYNTAX	INTEGER
			MAX-ACCESS	read-only
			STATUS	current
			::= { hmWanMbus13 45 }

hmWanMbus13VIF14		OBJECT-TYPE
			SYNTAX	INTEGER
			MAX-ACCESS	read-only
			STATUS	current
			::= { hmWanMbus13 46 }

hmWanMbus13Value14		OBJECT-TYPE
			SYNTAX	INTEGER
			MAX-ACCESS	read-only
			STATUS	current
			::= { hmWanMbus13 47 }

hmWanMbus13VIF15		OBJECT-TYPE
			SYNTAX	INTEGER
			MAX-ACCESS	read-only
			STATUS	current
			::= { hmWanMbus13 48 }

hmWanMbus13Value15		OBJECT-TYPE
			SYNTAX	INTEGER
			MAX-ACCESS	read-only
			STATUS	current
			::= { hmWanMbus13 49 }

hmWanMbus13VIF16		OBJECT-TYPE
			SYNTAX	INTEGER
			MAX-ACCESS	read-only
			STATUS	current
			::= { hmWanMbus13 50 }

hmWanMbus13Value16		OBJECT-TYPE
			SYNTAX	INTEGER
			MAX-ACCESS	read-only
			STATUS	current
			::= { hmWanMbus13 51 }

hmWanMbus13VIF17		OBJECT-TYPE
			SYNTAX	INTEGER
			MAX-ACCESS	read-only
			STATUS	current
			::= { hmWanMbus13 52 }

hmWanMbus13Value17		OBJECT-TYPE
			SYNTAX	INTEGER
			MAX-ACCESS	read-only
			STATUS	current
			::= { hmWanMbus13 53 }

hmWanMbus13VIF18		OBJECT-TYPE
			SYNTAX	INTEGER
			MAX-ACCESS	read-only
			STATUS	current
			::= { hmWanMbus13 54 }

hmWanMbus13Value18		OBJECT-TYPE
			SYNTAX	INTEGER
			MAX-ACCESS	read-only
			STATUS	current
			::= { hmWanMbus13 55 }

hmWanMbus13VIF19		OBJECT-TYPE
			SYNTAX	INTEGER
			MAX-ACCESS	read-only
			STATUS	current
			::= { hmWanMbus13 56 }

hmWanMbus13Value19		OBJECT-TYPE
			SYNTAX	INTEGER
			MAX-ACCESS	read-only
			STATUS	current
			::= { hmWanMbus13 57 }

hmWanMbus13VIF1A		OBJECT-TYPE
			SYNTAX	INTEGER
			MAX-ACCESS	read-only
			STATUS	current
			::= { hmWanMbus13 58 }

hmWanMbus13Value1A		OBJECT-TYPE
			SYNTAX	INTEGER
			MAX-ACCESS	read-only
			STATUS	current
			::= { hmWanMbus13 59 }

hmWanMbus13VIF1B		OBJECT-TYPE
			SYNTAX	INTEGER
			MAX-ACCESS	read-only
			STATUS	current
			::= { hmWanMbus13 60 }

hmWanMbus13Value1B		OBJECT-TYPE
			SYNTAX	INTEGER
			MAX-ACCESS	read-only
			STATUS	current
			::= { hmWanMbus13 61 }

hmWanMbus13VIF1C		OBJECT-TYPE
			SYNTAX	INTEGER
			MAX-ACCESS	read-only
			STATUS	current
			::= { hmWanMbus13 62 }

hmWanMbus13Value1C		OBJECT-TYPE
			SYNTAX	INTEGER
			MAX-ACCESS	read-only
			STATUS	current
			::= { hmWanMbus13 63 }

hmWanMbus13VIF1D		OBJECT-TYPE
			SYNTAX	INTEGER
			MAX-ACCESS	read-only
			STATUS	current
			::= { hmWanMbus13 64 }

hmWanMbus13Value1D		OBJECT-TYPE
			SYNTAX	INTEGER
			MAX-ACCESS	read-only
			STATUS	current
			::= { hmWanMbus13 65 }

hmWanMbus13VIF1E		OBJECT-TYPE
			SYNTAX	INTEGER
			MAX-ACCESS	read-only
			STATUS	current
			::= { hmWanMbus13 66 }

hmWanMbus13Value1E		OBJECT-TYPE
			SYNTAX	INTEGER
			MAX-ACCESS	read-only
			STATUS	current
			::= { hmWanMbus13 67 }

hmWanMbus13VIF1F		OBJECT-TYPE
			SYNTAX	INTEGER
			MAX-ACCESS	read-only
			STATUS	current
			::= { hmWanMbus13 68 }

hmWanMbus13Value1F		OBJECT-TYPE
			SYNTAX	INTEGER
			MAX-ACCESS	read-only
			STATUS	current
			::= { hmWanMbus13 69 }

hmWanMbus13VIF20		OBJECT-TYPE
			SYNTAX	INTEGER
			MAX-ACCESS	read-only
			STATUS	current
			::= { hmWanMbus13 70 }

hmWanMbus13Value20		OBJECT-TYPE
			SYNTAX	INTEGER
			MAX-ACCESS	read-only
			STATUS	current
			::= { hmWanMbus13 71 }

hmWanMbus13VIF21		OBJECT-TYPE
			SYNTAX	INTEGER
			MAX-ACCESS	read-only
			STATUS	current
			::= { hmWanMbus13 72 }

hmWanMbus13Value21		OBJECT-TYPE
			SYNTAX	INTEGER
			MAX-ACCESS	read-only
			STATUS	current
			::= { hmWanMbus13 73 }

hmWanMbus13VIF22		OBJECT-TYPE
			SYNTAX	INTEGER
			MAX-ACCESS	read-only
			STATUS	current
			::= { hmWanMbus13 74 }

hmWanMbus13Value22		OBJECT-TYPE
			SYNTAX	INTEGER
			MAX-ACCESS	read-only
			STATUS	current
			::= { hmWanMbus13 75 }

hmWanMbus13VIF23		OBJECT-TYPE
			SYNTAX	INTEGER
			MAX-ACCESS	read-only
			STATUS	current
			::= { hmWanMbus13 76 }

hmWanMbus13Value23		OBJECT-TYPE
			SYNTAX	INTEGER
			MAX-ACCESS	read-only
			STATUS	current
			::= { hmWanMbus13 77 }

hmWanMbus13VIF24		OBJECT-TYPE
			SYNTAX	INTEGER
			MAX-ACCESS	read-only
			STATUS	current
			::= { hmWanMbus13 78 }

hmWanMbus13Value24		OBJECT-TYPE
			SYNTAX	INTEGER
			MAX-ACCESS	read-only
			STATUS	current
			::= { hmWanMbus13 79 }

hmWanMbus13VIF25		OBJECT-TYPE
			SYNTAX	INTEGER
			MAX-ACCESS	read-only
			STATUS	current
			::= { hmWanMbus13 80 }

hmWanMbus13Value25		OBJECT-TYPE
			SYNTAX	INTEGER
			MAX-ACCESS	read-only
			STATUS	current
			::= { hmWanMbus13 81 }

hmWanMbus13VIF26		OBJECT-TYPE
			SYNTAX	INTEGER
			MAX-ACCESS	read-only
			STATUS	current
			::= { hmWanMbus13 82 }

hmWanMbus13Value26		OBJECT-TYPE
			SYNTAX	INTEGER
			MAX-ACCESS	read-only
			STATUS	current
			::= { hmWanMbus13 83 }

hmWanMbus13VIF27		OBJECT-TYPE
			SYNTAX	INTEGER
			MAX-ACCESS	read-only
			STATUS	current
			::= { hmWanMbus13 84 }

hmWanMbus13Value27		OBJECT-TYPE
			SYNTAX	INTEGER
			MAX-ACCESS	read-only
			STATUS	current
			::= { hmWanMbus13 85 }

hmWanMbus13VIF28		OBJECT-TYPE
			SYNTAX	INTEGER
			MAX-ACCESS	read-only
			STATUS	current
			::= { hmWanMbus13 86 }

hmWanMbus13Value28		OBJECT-TYPE
			SYNTAX	INTEGER
			MAX-ACCESS	read-only
			STATUS	current
			::= { hmWanMbus13 87 }

hmWanMbus13VIF29		OBJECT-TYPE
			SYNTAX	INTEGER
			MAX-ACCESS	read-only
			STATUS	current
			::= { hmWanMbus13 88 }

hmWanMbus13Value29		OBJECT-TYPE
			SYNTAX	INTEGER
			MAX-ACCESS	read-only
			STATUS	current
			::= { hmWanMbus13 89 }

hmWanMbus13VIF2A		OBJECT-TYPE
			SYNTAX	INTEGER
			MAX-ACCESS	read-only
			STATUS	current
			::= { hmWanMbus13 90 }

hmWanMbus13Value2A		OBJECT-TYPE
			SYNTAX	INTEGER
			MAX-ACCESS	read-only
			STATUS	current
			::= { hmWanMbus13 91 }

hmWanMbus13VIF2B		OBJECT-TYPE
			SYNTAX	INTEGER
			MAX-ACCESS	read-only
			STATUS	current
			::= { hmWanMbus13 92 }

hmWanMbus13Value2B		OBJECT-TYPE
			SYNTAX	INTEGER
			MAX-ACCESS	read-only
			STATUS	current
			::= { hmWanMbus13 93 }

hmWanMbus13VIF2C		OBJECT-TYPE
			SYNTAX	INTEGER
			MAX-ACCESS	read-only
			STATUS	current
			::= { hmWanMbus13 94 }

hmWanMbus13Value2C		OBJECT-TYPE
			SYNTAX	INTEGER
			MAX-ACCESS	read-only
			STATUS	current
			::= { hmWanMbus13 95 }

hmWanMbus13VIF2D		OBJECT-TYPE
			SYNTAX	INTEGER
			MAX-ACCESS	read-only
			STATUS	current
			::= { hmWanMbus13 96 }

hmWanMbus13Value2D		OBJECT-TYPE
			SYNTAX	INTEGER
			MAX-ACCESS	read-only
			STATUS	current
			::= { hmWanMbus13 97 }

hmWanMbus13VIF2E		OBJECT-TYPE
			SYNTAX	INTEGER
			MAX-ACCESS	read-only
			STATUS	current
			::= { hmWanMbus13 98 }

hmWanMbus13Value2E		OBJECT-TYPE
			SYNTAX	INTEGER
			MAX-ACCESS	read-only
			STATUS	current
			::= { hmWanMbus13 99 }

hmWanMbus13VIF2F		OBJECT-TYPE
			SYNTAX	INTEGER
			MAX-ACCESS	read-only
			STATUS	current
			::= { hmWanMbus13 100 }

hmWanMbus13Value2F		OBJECT-TYPE
			SYNTAX	INTEGER
			MAX-ACCESS	read-only
			STATUS	current
			::= { hmWanMbus13 101 }

hmWanMbus14			OBJECT IDENTIFIER ::= { hmWanMbus 20 }

hmWanMbus14IdNumber		OBJECT-TYPE
			SYNTAX	Gauge32
			MAX-ACCESS	read-only
			STATUS	current
			::= { hmWanMbus14 1 }

hmWanMbus14Manufacturer	OBJECT-TYPE
			SYNTAX	Gauge32
			MAX-ACCESS	read-only
			STATUS	current
			::= { hmWanMbus14 2 }

hmWanMbus14Version		OBJECT-TYPE
			SYNTAX	Gauge32
			MAX-ACCESS	read-only
			STATUS	current
			::= { hmWanMbus14 3 }

hmWanMbus14Medium		OBJECT-TYPE
			SYNTAX	Gauge32
			MAX-ACCESS	read-only
			STATUS	current
			::= { hmWanMbus14 4 }

hmWanMbus14Status		OBJECT-TYPE
			SYNTAX	Gauge32
			MAX-ACCESS	read-only
			STATUS	current
			::= { hmWanMbus14 5 }

hmWanMbus14VIF00		OBJECT-TYPE
			SYNTAX	INTEGER
			MAX-ACCESS	read-only
			STATUS	current
			::= { hmWanMbus14 6 }

hmWanMbus14Value00		OBJECT-TYPE
			SYNTAX	INTEGER
			MAX-ACCESS	read-only
			STATUS	current
			::= { hmWanMbus14 7 }

hmWanMbus14VIF01		OBJECT-TYPE
			SYNTAX	INTEGER
			MAX-ACCESS	read-only
			STATUS	current
			::= { hmWanMbus14 8 }

hmWanMbus14Value01		OBJECT-TYPE
			SYNTAX	INTEGER
			MAX-ACCESS	read-only
			STATUS	current
			::= { hmWanMbus14 9 }

hmWanMbus14VIF02		OBJECT-TYPE
			SYNTAX	INTEGER
			MAX-ACCESS	read-only
			STATUS	current
			::= { hmWanMbus14 10 }

hmWanMbus14Value02		OBJECT-TYPE
			SYNTAX	INTEGER
			MAX-ACCESS	read-only
			STATUS	current
			::= { hmWanMbus14 11 }

hmWanMbus14VIF03		OBJECT-TYPE
			SYNTAX	INTEGER
			MAX-ACCESS	read-only
			STATUS	current
			::= { hmWanMbus14 12 }

hmWanMbus14Value03		OBJECT-TYPE
			SYNTAX	INTEGER
			MAX-ACCESS	read-only
			STATUS	current
			::= { hmWanMbus14 13 }

hmWanMbus14VIF04		OBJECT-TYPE
			SYNTAX	INTEGER
			MAX-ACCESS	read-only
			STATUS	current
			::= { hmWanMbus14 14 }

hmWanMbus14Value04		OBJECT-TYPE
			SYNTAX	INTEGER
			MAX-ACCESS	read-only
			STATUS	current
			::= { hmWanMbus14 15 }

hmWanMbus14VIF05		OBJECT-TYPE
			SYNTAX	INTEGER
			MAX-ACCESS	read-only
			STATUS	current
			::= { hmWanMbus14 16 }

hmWanMbus14Value05		OBJECT-TYPE
			SYNTAX	INTEGER
			MAX-ACCESS	read-only
			STATUS	current
			::= { hmWanMbus14 17 }

hmWanMbus14VIF06		OBJECT-TYPE
			SYNTAX	INTEGER
			MAX-ACCESS	read-only
			STATUS	current
			::= { hmWanMbus14 18 }

hmWanMbus14Value06		OBJECT-TYPE
			SYNTAX	INTEGER
			MAX-ACCESS	read-only
			STATUS	current
			::= { hmWanMbus14 19 }

hmWanMbus14VIF07		OBJECT-TYPE
			SYNTAX	INTEGER
			MAX-ACCESS	read-only
			STATUS	current
			::= { hmWanMbus14 20 }

hmWanMbus14Value07		OBJECT-TYPE
			SYNTAX	INTEGER
			MAX-ACCESS	read-only
			STATUS	current
			::= { hmWanMbus14 21 }

hmWanMbus14VIF08		OBJECT-TYPE
			SYNTAX	INTEGER
			MAX-ACCESS	read-only
			STATUS	current
			::= { hmWanMbus14 22 }

hmWanMbus14Value08		OBJECT-TYPE
			SYNTAX	INTEGER
			MAX-ACCESS	read-only
			STATUS	current
			::= { hmWanMbus14 23 }

hmWanMbus14VIF09		OBJECT-TYPE
			SYNTAX	INTEGER
			MAX-ACCESS	read-only
			STATUS	current
			::= { hmWanMbus14 24 }

hmWanMbus14Value09		OBJECT-TYPE
			SYNTAX	INTEGER
			MAX-ACCESS	read-only
			STATUS	current
			::= { hmWanMbus14 25 }

hmWanMbus14VIF0A		OBJECT-TYPE
			SYNTAX	INTEGER
			MAX-ACCESS	read-only
			STATUS	current
			::= { hmWanMbus14 26 }

hmWanMbus14Value0A		OBJECT-TYPE
			SYNTAX	INTEGER
			MAX-ACCESS	read-only
			STATUS	current
			::= { hmWanMbus14 27 }

hmWanMbus14VIF0B		OBJECT-TYPE
			SYNTAX	INTEGER
			MAX-ACCESS	read-only
			STATUS	current
			::= { hmWanMbus14 28 }

hmWanMbus14Value0B		OBJECT-TYPE
			SYNTAX	INTEGER
			MAX-ACCESS	read-only
			STATUS	current
			::= { hmWanMbus14 29 }

hmWanMbus14VIF0C		OBJECT-TYPE
			SYNTAX	INTEGER
			MAX-ACCESS	read-only
			STATUS	current
			::= { hmWanMbus14 30 }

hmWanMbus14Value0C		OBJECT-TYPE
			SYNTAX	INTEGER
			MAX-ACCESS	read-only
			STATUS	current
			::= { hmWanMbus14 31 }

hmWanMbus14VIF0D		OBJECT-TYPE
			SYNTAX	INTEGER
			MAX-ACCESS	read-only
			STATUS	current
			::= { hmWanMbus14 32 }

hmWanMbus14Value0D		OBJECT-TYPE
			SYNTAX	INTEGER
			MAX-ACCESS	read-only
			STATUS	current
			::= { hmWanMbus14 33 }

hmWanMbus14VIF0E		OBJECT-TYPE
			SYNTAX	INTEGER
			MAX-ACCESS	read-only
			STATUS	current
			::= { hmWanMbus14 34 }

hmWanMbus14Value0E		OBJECT-TYPE
			SYNTAX	INTEGER
			MAX-ACCESS	read-only
			STATUS	current
			::= { hmWanMbus14 35 }

hmWanMbus14VIF0F		OBJECT-TYPE
			SYNTAX	INTEGER
			MAX-ACCESS	read-only
			STATUS	current
			::= { hmWanMbus14 36 }

hmWanMbus14Value0F		OBJECT-TYPE
			SYNTAX	INTEGER
			MAX-ACCESS	read-only
			STATUS	current
			::= { hmWanMbus14 37 }

hmWanMbus14VIF10		OBJECT-TYPE
			SYNTAX	INTEGER
			MAX-ACCESS	read-only
			STATUS	current
			::= { hmWanMbus14 38 }

hmWanMbus14Value10		OBJECT-TYPE
			SYNTAX	INTEGER
			MAX-ACCESS	read-only
			STATUS	current
			::= { hmWanMbus14 39 }

hmWanMbus14VIF11		OBJECT-TYPE
			SYNTAX	INTEGER
			MAX-ACCESS	read-only
			STATUS	current
			::= { hmWanMbus14 40 }

hmWanMbus14Value11		OBJECT-TYPE
			SYNTAX	INTEGER
			MAX-ACCESS	read-only
			STATUS	current
			::= { hmWanMbus14 41 }

hmWanMbus14VIF12		OBJECT-TYPE
			SYNTAX	INTEGER
			MAX-ACCESS	read-only
			STATUS	current
			::= { hmWanMbus14 42 }

hmWanMbus14Value12		OBJECT-TYPE
			SYNTAX	INTEGER
			MAX-ACCESS	read-only
			STATUS	current
			::= { hmWanMbus14 43 }

hmWanMbus14VIF13		OBJECT-TYPE
			SYNTAX	INTEGER
			MAX-ACCESS	read-only
			STATUS	current
			::= { hmWanMbus14 44 }

hmWanMbus14Value13		OBJECT-TYPE
			SYNTAX	INTEGER
			MAX-ACCESS	read-only
			STATUS	current
			::= { hmWanMbus14 45 }

hmWanMbus14VIF14		OBJECT-TYPE
			SYNTAX	INTEGER
			MAX-ACCESS	read-only
			STATUS	current
			::= { hmWanMbus14 46 }

hmWanMbus14Value14		OBJECT-TYPE
			SYNTAX	INTEGER
			MAX-ACCESS	read-only
			STATUS	current
			::= { hmWanMbus14 47 }

hmWanMbus14VIF15		OBJECT-TYPE
			SYNTAX	INTEGER
			MAX-ACCESS	read-only
			STATUS	current
			::= { hmWanMbus14 48 }

hmWanMbus14Value15		OBJECT-TYPE
			SYNTAX	INTEGER
			MAX-ACCESS	read-only
			STATUS	current
			::= { hmWanMbus14 49 }

hmWanMbus14VIF16		OBJECT-TYPE
			SYNTAX	INTEGER
			MAX-ACCESS	read-only
			STATUS	current
			::= { hmWanMbus14 50 }

hmWanMbus14Value16		OBJECT-TYPE
			SYNTAX	INTEGER
			MAX-ACCESS	read-only
			STATUS	current
			::= { hmWanMbus14 51 }

hmWanMbus14VIF17		OBJECT-TYPE
			SYNTAX	INTEGER
			MAX-ACCESS	read-only
			STATUS	current
			::= { hmWanMbus14 52 }

hmWanMbus14Value17		OBJECT-TYPE
			SYNTAX	INTEGER
			MAX-ACCESS	read-only
			STATUS	current
			::= { hmWanMbus14 53 }

hmWanMbus14VIF18		OBJECT-TYPE
			SYNTAX	INTEGER
			MAX-ACCESS	read-only
			STATUS	current
			::= { hmWanMbus14 54 }

hmWanMbus14Value18		OBJECT-TYPE
			SYNTAX	INTEGER
			MAX-ACCESS	read-only
			STATUS	current
			::= { hmWanMbus14 55 }

hmWanMbus14VIF19		OBJECT-TYPE
			SYNTAX	INTEGER
			MAX-ACCESS	read-only
			STATUS	current
			::= { hmWanMbus14 56 }

hmWanMbus14Value19		OBJECT-TYPE
			SYNTAX	INTEGER
			MAX-ACCESS	read-only
			STATUS	current
			::= { hmWanMbus14 57 }

hmWanMbus14VIF1A		OBJECT-TYPE
			SYNTAX	INTEGER
			MAX-ACCESS	read-only
			STATUS	current
			::= { hmWanMbus14 58 }

hmWanMbus14Value1A		OBJECT-TYPE
			SYNTAX	INTEGER
			MAX-ACCESS	read-only
			STATUS	current
			::= { hmWanMbus14 59 }

hmWanMbus14VIF1B		OBJECT-TYPE
			SYNTAX	INTEGER
			MAX-ACCESS	read-only
			STATUS	current
			::= { hmWanMbus14 60 }

hmWanMbus14Value1B		OBJECT-TYPE
			SYNTAX	INTEGER
			MAX-ACCESS	read-only
			STATUS	current
			::= { hmWanMbus14 61 }

hmWanMbus14VIF1C		OBJECT-TYPE
			SYNTAX	INTEGER
			MAX-ACCESS	read-only
			STATUS	current
			::= { hmWanMbus14 62 }

hmWanMbus14Value1C		OBJECT-TYPE
			SYNTAX	INTEGER
			MAX-ACCESS	read-only
			STATUS	current
			::= { hmWanMbus14 63 }

hmWanMbus14VIF1D		OBJECT-TYPE
			SYNTAX	INTEGER
			MAX-ACCESS	read-only
			STATUS	current
			::= { hmWanMbus14 64 }

hmWanMbus14Value1D		OBJECT-TYPE
			SYNTAX	INTEGER
			MAX-ACCESS	read-only
			STATUS	current
			::= { hmWanMbus14 65 }

hmWanMbus14VIF1E		OBJECT-TYPE
			SYNTAX	INTEGER
			MAX-ACCESS	read-only
			STATUS	current
			::= { hmWanMbus14 66 }

hmWanMbus14Value1E		OBJECT-TYPE
			SYNTAX	INTEGER
			MAX-ACCESS	read-only
			STATUS	current
			::= { hmWanMbus14 67 }

hmWanMbus14VIF1F		OBJECT-TYPE
			SYNTAX	INTEGER
			MAX-ACCESS	read-only
			STATUS	current
			::= { hmWanMbus14 68 }

hmWanMbus14Value1F		OBJECT-TYPE
			SYNTAX	INTEGER
			MAX-ACCESS	read-only
			STATUS	current
			::= { hmWanMbus14 69 }

hmWanMbus14VIF20		OBJECT-TYPE
			SYNTAX	INTEGER
			MAX-ACCESS	read-only
			STATUS	current
			::= { hmWanMbus14 70 }

hmWanMbus14Value20		OBJECT-TYPE
			SYNTAX	INTEGER
			MAX-ACCESS	read-only
			STATUS	current
			::= { hmWanMbus14 71 }

hmWanMbus14VIF21		OBJECT-TYPE
			SYNTAX	INTEGER
			MAX-ACCESS	read-only
			STATUS	current
			::= { hmWanMbus14 72 }

hmWanMbus14Value21		OBJECT-TYPE
			SYNTAX	INTEGER
			MAX-ACCESS	read-only
			STATUS	current
			::= { hmWanMbus14 73 }

hmWanMbus14VIF22		OBJECT-TYPE
			SYNTAX	INTEGER
			MAX-ACCESS	read-only
			STATUS	current
			::= { hmWanMbus14 74 }

hmWanMbus14Value22		OBJECT-TYPE
			SYNTAX	INTEGER
			MAX-ACCESS	read-only
			STATUS	current
			::= { hmWanMbus14 75 }

hmWanMbus14VIF23		OBJECT-TYPE
			SYNTAX	INTEGER
			MAX-ACCESS	read-only
			STATUS	current
			::= { hmWanMbus14 76 }

hmWanMbus14Value23		OBJECT-TYPE
			SYNTAX	INTEGER
			MAX-ACCESS	read-only
			STATUS	current
			::= { hmWanMbus14 77 }

hmWanMbus14VIF24		OBJECT-TYPE
			SYNTAX	INTEGER
			MAX-ACCESS	read-only
			STATUS	current
			::= { hmWanMbus14 78 }

hmWanMbus14Value24		OBJECT-TYPE
			SYNTAX	INTEGER
			MAX-ACCESS	read-only
			STATUS	current
			::= { hmWanMbus14 79 }

hmWanMbus14VIF25		OBJECT-TYPE
			SYNTAX	INTEGER
			MAX-ACCESS	read-only
			STATUS	current
			::= { hmWanMbus14 80 }

hmWanMbus14Value25		OBJECT-TYPE
			SYNTAX	INTEGER
			MAX-ACCESS	read-only
			STATUS	current
			::= { hmWanMbus14 81 }

hmWanMbus14VIF26		OBJECT-TYPE
			SYNTAX	INTEGER
			MAX-ACCESS	read-only
			STATUS	current
			::= { hmWanMbus14 82 }

hmWanMbus14Value26		OBJECT-TYPE
			SYNTAX	INTEGER
			MAX-ACCESS	read-only
			STATUS	current
			::= { hmWanMbus14 83 }

hmWanMbus14VIF27		OBJECT-TYPE
			SYNTAX	INTEGER
			MAX-ACCESS	read-only
			STATUS	current
			::= { hmWanMbus14 84 }

hmWanMbus14Value27		OBJECT-TYPE
			SYNTAX	INTEGER
			MAX-ACCESS	read-only
			STATUS	current
			::= { hmWanMbus14 85 }

hmWanMbus14VIF28		OBJECT-TYPE
			SYNTAX	INTEGER
			MAX-ACCESS	read-only
			STATUS	current
			::= { hmWanMbus14 86 }

hmWanMbus14Value28		OBJECT-TYPE
			SYNTAX	INTEGER
			MAX-ACCESS	read-only
			STATUS	current
			::= { hmWanMbus14 87 }

hmWanMbus14VIF29		OBJECT-TYPE
			SYNTAX	INTEGER
			MAX-ACCESS	read-only
			STATUS	current
			::= { hmWanMbus14 88 }

hmWanMbus14Value29		OBJECT-TYPE
			SYNTAX	INTEGER
			MAX-ACCESS	read-only
			STATUS	current
			::= { hmWanMbus14 89 }

hmWanMbus14VIF2A		OBJECT-TYPE
			SYNTAX	INTEGER
			MAX-ACCESS	read-only
			STATUS	current
			::= { hmWanMbus14 90 }

hmWanMbus14Value2A		OBJECT-TYPE
			SYNTAX	INTEGER
			MAX-ACCESS	read-only
			STATUS	current
			::= { hmWanMbus14 91 }

hmWanMbus14VIF2B		OBJECT-TYPE
			SYNTAX	INTEGER
			MAX-ACCESS	read-only
			STATUS	current
			::= { hmWanMbus14 92 }

hmWanMbus14Value2B		OBJECT-TYPE
			SYNTAX	INTEGER
			MAX-ACCESS	read-only
			STATUS	current
			::= { hmWanMbus14 93 }

hmWanMbus14VIF2C		OBJECT-TYPE
			SYNTAX	INTEGER
			MAX-ACCESS	read-only
			STATUS	current
			::= { hmWanMbus14 94 }

hmWanMbus14Value2C		OBJECT-TYPE
			SYNTAX	INTEGER
			MAX-ACCESS	read-only
			STATUS	current
			::= { hmWanMbus14 95 }

hmWanMbus14VIF2D		OBJECT-TYPE
			SYNTAX	INTEGER
			MAX-ACCESS	read-only
			STATUS	current
			::= { hmWanMbus14 96 }

hmWanMbus14Value2D		OBJECT-TYPE
			SYNTAX	INTEGER
			MAX-ACCESS	read-only
			STATUS	current
			::= { hmWanMbus14 97 }

hmWanMbus14VIF2E		OBJECT-TYPE
			SYNTAX	INTEGER
			MAX-ACCESS	read-only
			STATUS	current
			::= { hmWanMbus14 98 }

hmWanMbus14Value2E		OBJECT-TYPE
			SYNTAX	INTEGER
			MAX-ACCESS	read-only
			STATUS	current
			::= { hmWanMbus14 99 }

hmWanMbus14VIF2F		OBJECT-TYPE
			SYNTAX	INTEGER
			MAX-ACCESS	read-only
			STATUS	current
			::= { hmWanMbus14 100 }

hmWanMbus14Value2F		OBJECT-TYPE
			SYNTAX	INTEGER
			MAX-ACCESS	read-only
			STATUS	current
			::= { hmWanMbus14 101 }

hmWanMbus15			OBJECT IDENTIFIER ::= { hmWanMbus 21 }

hmWanMbus15IdNumber		OBJECT-TYPE
			SYNTAX	Gauge32
			MAX-ACCESS	read-only
			STATUS	current
			::= { hmWanMbus15 1 }

hmWanMbus15Manufacturer	OBJECT-TYPE
			SYNTAX	Gauge32
			MAX-ACCESS	read-only
			STATUS	current
			::= { hmWanMbus15 2 }

hmWanMbus15Version		OBJECT-TYPE
			SYNTAX	Gauge32
			MAX-ACCESS	read-only
			STATUS	current
			::= { hmWanMbus15 3 }

hmWanMbus15Medium		OBJECT-TYPE
			SYNTAX	Gauge32
			MAX-ACCESS	read-only
			STATUS	current
			::= { hmWanMbus15 4 }

hmWanMbus15Status		OBJECT-TYPE
			SYNTAX	Gauge32
			MAX-ACCESS	read-only
			STATUS	current
			::= { hmWanMbus15 5 }

hmWanMbus15VIF00		OBJECT-TYPE
			SYNTAX	INTEGER
			MAX-ACCESS	read-only
			STATUS	current
			::= { hmWanMbus15 6 }

hmWanMbus15Value00		OBJECT-TYPE
			SYNTAX	INTEGER
			MAX-ACCESS	read-only
			STATUS	current
			::= { hmWanMbus15 7 }

hmWanMbus15VIF01		OBJECT-TYPE
			SYNTAX	INTEGER
			MAX-ACCESS	read-only
			STATUS	current
			::= { hmWanMbus15 8 }

hmWanMbus15Value01		OBJECT-TYPE
			SYNTAX	INTEGER
			MAX-ACCESS	read-only
			STATUS	current
			::= { hmWanMbus15 9 }

hmWanMbus15VIF02		OBJECT-TYPE
			SYNTAX	INTEGER
			MAX-ACCESS	read-only
			STATUS	current
			::= { hmWanMbus15 10 }

hmWanMbus15Value02		OBJECT-TYPE
			SYNTAX	INTEGER
			MAX-ACCESS	read-only
			STATUS	current
			::= { hmWanMbus15 11 }

hmWanMbus15VIF03		OBJECT-TYPE
			SYNTAX	INTEGER
			MAX-ACCESS	read-only
			STATUS	current
			::= { hmWanMbus15 12 }

hmWanMbus15Value03		OBJECT-TYPE
			SYNTAX	INTEGER
			MAX-ACCESS	read-only
			STATUS	current
			::= { hmWanMbus15 13 }

hmWanMbus15VIF04		OBJECT-TYPE
			SYNTAX	INTEGER
			MAX-ACCESS	read-only
			STATUS	current
			::= { hmWanMbus15 14 }

hmWanMbus15Value04		OBJECT-TYPE
			SYNTAX	INTEGER
			MAX-ACCESS	read-only
			STATUS	current
			::= { hmWanMbus15 15 }

hmWanMbus15VIF05		OBJECT-TYPE
			SYNTAX	INTEGER
			MAX-ACCESS	read-only
			STATUS	current
			::= { hmWanMbus15 16 }

hmWanMbus15Value05		OBJECT-TYPE
			SYNTAX	INTEGER
			MAX-ACCESS	read-only
			STATUS	current
			::= { hmWanMbus15 17 }

hmWanMbus15VIF06		OBJECT-TYPE
			SYNTAX	INTEGER
			MAX-ACCESS	read-only
			STATUS	current
			::= { hmWanMbus15 18 }

hmWanMbus15Value06		OBJECT-TYPE
			SYNTAX	INTEGER
			MAX-ACCESS	read-only
			STATUS	current
			::= { hmWanMbus15 19 }

hmWanMbus15VIF07		OBJECT-TYPE
			SYNTAX	INTEGER
			MAX-ACCESS	read-only
			STATUS	current
			::= { hmWanMbus15 20 }

hmWanMbus15Value07		OBJECT-TYPE
			SYNTAX	INTEGER
			MAX-ACCESS	read-only
			STATUS	current
			::= { hmWanMbus15 21 }

hmWanMbus15VIF08		OBJECT-TYPE
			SYNTAX	INTEGER
			MAX-ACCESS	read-only
			STATUS	current
			::= { hmWanMbus15 22 }

hmWanMbus15Value08		OBJECT-TYPE
			SYNTAX	INTEGER
			MAX-ACCESS	read-only
			STATUS	current
			::= { hmWanMbus15 23 }

hmWanMbus15VIF09		OBJECT-TYPE
			SYNTAX	INTEGER
			MAX-ACCESS	read-only
			STATUS	current
			::= { hmWanMbus15 24 }

hmWanMbus15Value09		OBJECT-TYPE
			SYNTAX	INTEGER
			MAX-ACCESS	read-only
			STATUS	current
			::= { hmWanMbus15 25 }

hmWanMbus15VIF0A		OBJECT-TYPE
			SYNTAX	INTEGER
			MAX-ACCESS	read-only
			STATUS	current
			::= { hmWanMbus15 26 }

hmWanMbus15Value0A		OBJECT-TYPE
			SYNTAX	INTEGER
			MAX-ACCESS	read-only
			STATUS	current
			::= { hmWanMbus15 27 }

hmWanMbus15VIF0B		OBJECT-TYPE
			SYNTAX	INTEGER
			MAX-ACCESS	read-only
			STATUS	current
			::= { hmWanMbus15 28 }

hmWanMbus15Value0B		OBJECT-TYPE
			SYNTAX	INTEGER
			MAX-ACCESS	read-only
			STATUS	current
			::= { hmWanMbus15 29 }

hmWanMbus15VIF0C		OBJECT-TYPE
			SYNTAX	INTEGER
			MAX-ACCESS	read-only
			STATUS	current
			::= { hmWanMbus15 30 }

hmWanMbus15Value0C		OBJECT-TYPE
			SYNTAX	INTEGER
			MAX-ACCESS	read-only
			STATUS	current
			::= { hmWanMbus15 31 }

hmWanMbus15VIF0D		OBJECT-TYPE
			SYNTAX	INTEGER
			MAX-ACCESS	read-only
			STATUS	current
			::= { hmWanMbus15 32 }

hmWanMbus15Value0D		OBJECT-TYPE
			SYNTAX	INTEGER
			MAX-ACCESS	read-only
			STATUS	current
			::= { hmWanMbus15 33 }

hmWanMbus15VIF0E		OBJECT-TYPE
			SYNTAX	INTEGER
			MAX-ACCESS	read-only
			STATUS	current
			::= { hmWanMbus15 34 }

hmWanMbus15Value0E		OBJECT-TYPE
			SYNTAX	INTEGER
			MAX-ACCESS	read-only
			STATUS	current
			::= { hmWanMbus15 35 }

hmWanMbus15VIF0F		OBJECT-TYPE
			SYNTAX	INTEGER
			MAX-ACCESS	read-only
			STATUS	current
			::= { hmWanMbus15 36 }

hmWanMbus15Value0F		OBJECT-TYPE
			SYNTAX	INTEGER
			MAX-ACCESS	read-only
			STATUS	current
			::= { hmWanMbus15 37 }

hmWanMbus15VIF10		OBJECT-TYPE
			SYNTAX	INTEGER
			MAX-ACCESS	read-only
			STATUS	current
			::= { hmWanMbus15 38 }

hmWanMbus15Value10		OBJECT-TYPE
			SYNTAX	INTEGER
			MAX-ACCESS	read-only
			STATUS	current
			::= { hmWanMbus15 39 }

hmWanMbus15VIF11		OBJECT-TYPE
			SYNTAX	INTEGER
			MAX-ACCESS	read-only
			STATUS	current
			::= { hmWanMbus15 40 }

hmWanMbus15Value11		OBJECT-TYPE
			SYNTAX	INTEGER
			MAX-ACCESS	read-only
			STATUS	current
			::= { hmWanMbus15 41 }

hmWanMbus15VIF12		OBJECT-TYPE
			SYNTAX	INTEGER
			MAX-ACCESS	read-only
			STATUS	current
			::= { hmWanMbus15 42 }

hmWanMbus15Value12		OBJECT-TYPE
			SYNTAX	INTEGER
			MAX-ACCESS	read-only
			STATUS	current
			::= { hmWanMbus15 43 }

hmWanMbus15VIF13		OBJECT-TYPE
			SYNTAX	INTEGER
			MAX-ACCESS	read-only
			STATUS	current
			::= { hmWanMbus15 44 }

hmWanMbus15Value13		OBJECT-TYPE
			SYNTAX	INTEGER
			MAX-ACCESS	read-only
			STATUS	current
			::= { hmWanMbus15 45 }

hmWanMbus15VIF14		OBJECT-TYPE
			SYNTAX	INTEGER
			MAX-ACCESS	read-only
			STATUS	current
			::= { hmWanMbus15 46 }

hmWanMbus15Value14		OBJECT-TYPE
			SYNTAX	INTEGER
			MAX-ACCESS	read-only
			STATUS	current
			::= { hmWanMbus15 47 }

hmWanMbus15VIF15		OBJECT-TYPE
			SYNTAX	INTEGER
			MAX-ACCESS	read-only
			STATUS	current
			::= { hmWanMbus15 48 }

hmWanMbus15Value15		OBJECT-TYPE
			SYNTAX	INTEGER
			MAX-ACCESS	read-only
			STATUS	current
			::= { hmWanMbus15 49 }

hmWanMbus15VIF16		OBJECT-TYPE
			SYNTAX	INTEGER
			MAX-ACCESS	read-only
			STATUS	current
			::= { hmWanMbus15 50 }

hmWanMbus15Value16		OBJECT-TYPE
			SYNTAX	INTEGER
			MAX-ACCESS	read-only
			STATUS	current
			::= { hmWanMbus15 51 }

hmWanMbus15VIF17		OBJECT-TYPE
			SYNTAX	INTEGER
			MAX-ACCESS	read-only
			STATUS	current
			::= { hmWanMbus15 52 }

hmWanMbus15Value17		OBJECT-TYPE
			SYNTAX	INTEGER
			MAX-ACCESS	read-only
			STATUS	current
			::= { hmWanMbus15 53 }

hmWanMbus15VIF18		OBJECT-TYPE
			SYNTAX	INTEGER
			MAX-ACCESS	read-only
			STATUS	current
			::= { hmWanMbus15 54 }

hmWanMbus15Value18		OBJECT-TYPE
			SYNTAX	INTEGER
			MAX-ACCESS	read-only
			STATUS	current
			::= { hmWanMbus15 55 }

hmWanMbus15VIF19		OBJECT-TYPE
			SYNTAX	INTEGER
			MAX-ACCESS	read-only
			STATUS	current
			::= { hmWanMbus15 56 }

hmWanMbus15Value19		OBJECT-TYPE
			SYNTAX	INTEGER
			MAX-ACCESS	read-only
			STATUS	current
			::= { hmWanMbus15 57 }

hmWanMbus15VIF1A		OBJECT-TYPE
			SYNTAX	INTEGER
			MAX-ACCESS	read-only
			STATUS	current
			::= { hmWanMbus15 58 }

hmWanMbus15Value1A		OBJECT-TYPE
			SYNTAX	INTEGER
			MAX-ACCESS	read-only
			STATUS	current
			::= { hmWanMbus15 59 }

hmWanMbus15VIF1B		OBJECT-TYPE
			SYNTAX	INTEGER
			MAX-ACCESS	read-only
			STATUS	current
			::= { hmWanMbus15 60 }

hmWanMbus15Value1B		OBJECT-TYPE
			SYNTAX	INTEGER
			MAX-ACCESS	read-only
			STATUS	current
			::= { hmWanMbus15 61 }

hmWanMbus15VIF1C		OBJECT-TYPE
			SYNTAX	INTEGER
			MAX-ACCESS	read-only
			STATUS	current
			::= { hmWanMbus15 62 }

hmWanMbus15Value1C		OBJECT-TYPE
			SYNTAX	INTEGER
			MAX-ACCESS	read-only
			STATUS	current
			::= { hmWanMbus15 63 }

hmWanMbus15VIF1D		OBJECT-TYPE
			SYNTAX	INTEGER
			MAX-ACCESS	read-only
			STATUS	current
			::= { hmWanMbus15 64 }

hmWanMbus15Value1D		OBJECT-TYPE
			SYNTAX	INTEGER
			MAX-ACCESS	read-only
			STATUS	current
			::= { hmWanMbus15 65 }

hmWanMbus15VIF1E		OBJECT-TYPE
			SYNTAX	INTEGER
			MAX-ACCESS	read-only
			STATUS	current
			::= { hmWanMbus15 66 }

hmWanMbus15Value1E		OBJECT-TYPE
			SYNTAX	INTEGER
			MAX-ACCESS	read-only
			STATUS	current
			::= { hmWanMbus15 67 }

hmWanMbus15VIF1F		OBJECT-TYPE
			SYNTAX	INTEGER
			MAX-ACCESS	read-only
			STATUS	current
			::= { hmWanMbus15 68 }

hmWanMbus15Value1F		OBJECT-TYPE
			SYNTAX	INTEGER
			MAX-ACCESS	read-only
			STATUS	current
			::= { hmWanMbus15 69 }

hmWanMbus15VIF20		OBJECT-TYPE
			SYNTAX	INTEGER
			MAX-ACCESS	read-only
			STATUS	current
			::= { hmWanMbus15 70 }

hmWanMbus15Value20		OBJECT-TYPE
			SYNTAX	INTEGER
			MAX-ACCESS	read-only
			STATUS	current
			::= { hmWanMbus15 71 }

hmWanMbus15VIF21		OBJECT-TYPE
			SYNTAX	INTEGER
			MAX-ACCESS	read-only
			STATUS	current
			::= { hmWanMbus15 72 }

hmWanMbus15Value21		OBJECT-TYPE
			SYNTAX	INTEGER
			MAX-ACCESS	read-only
			STATUS	current
			::= { hmWanMbus15 73 }

hmWanMbus15VIF22		OBJECT-TYPE
			SYNTAX	INTEGER
			MAX-ACCESS	read-only
			STATUS	current
			::= { hmWanMbus15 74 }

hmWanMbus15Value22		OBJECT-TYPE
			SYNTAX	INTEGER
			MAX-ACCESS	read-only
			STATUS	current
			::= { hmWanMbus15 75 }

hmWanMbus15VIF23		OBJECT-TYPE
			SYNTAX	INTEGER
			MAX-ACCESS	read-only
			STATUS	current
			::= { hmWanMbus15 76 }

hmWanMbus15Value23		OBJECT-TYPE
			SYNTAX	INTEGER
			MAX-ACCESS	read-only
			STATUS	current
			::= { hmWanMbus15 77 }

hmWanMbus15VIF24		OBJECT-TYPE
			SYNTAX	INTEGER
			MAX-ACCESS	read-only
			STATUS	current
			::= { hmWanMbus15 78 }

hmWanMbus15Value24		OBJECT-TYPE
			SYNTAX	INTEGER
			MAX-ACCESS	read-only
			STATUS	current
			::= { hmWanMbus15 79 }

hmWanMbus15VIF25		OBJECT-TYPE
			SYNTAX	INTEGER
			MAX-ACCESS	read-only
			STATUS	current
			::= { hmWanMbus15 80 }

hmWanMbus15Value25		OBJECT-TYPE
			SYNTAX	INTEGER
			MAX-ACCESS	read-only
			STATUS	current
			::= { hmWanMbus15 81 }

hmWanMbus15VIF26		OBJECT-TYPE
			SYNTAX	INTEGER
			MAX-ACCESS	read-only
			STATUS	current
			::= { hmWanMbus15 82 }

hmWanMbus15Value26		OBJECT-TYPE
			SYNTAX	INTEGER
			MAX-ACCESS	read-only
			STATUS	current
			::= { hmWanMbus15 83 }

hmWanMbus15VIF27		OBJECT-TYPE
			SYNTAX	INTEGER
			MAX-ACCESS	read-only
			STATUS	current
			::= { hmWanMbus15 84 }

hmWanMbus15Value27		OBJECT-TYPE
			SYNTAX	INTEGER
			MAX-ACCESS	read-only
			STATUS	current
			::= { hmWanMbus15 85 }

hmWanMbus15VIF28		OBJECT-TYPE
			SYNTAX	INTEGER
			MAX-ACCESS	read-only
			STATUS	current
			::= { hmWanMbus15 86 }

hmWanMbus15Value28		OBJECT-TYPE
			SYNTAX	INTEGER
			MAX-ACCESS	read-only
			STATUS	current
			::= { hmWanMbus15 87 }

hmWanMbus15VIF29		OBJECT-TYPE
			SYNTAX	INTEGER
			MAX-ACCESS	read-only
			STATUS	current
			::= { hmWanMbus15 88 }

hmWanMbus15Value29		OBJECT-TYPE
			SYNTAX	INTEGER
			MAX-ACCESS	read-only
			STATUS	current
			::= { hmWanMbus15 89 }

hmWanMbus15VIF2A		OBJECT-TYPE
			SYNTAX	INTEGER
			MAX-ACCESS	read-only
			STATUS	current
			::= { hmWanMbus15 90 }

hmWanMbus15Value2A		OBJECT-TYPE
			SYNTAX	INTEGER
			MAX-ACCESS	read-only
			STATUS	current
			::= { hmWanMbus15 91 }

hmWanMbus15VIF2B		OBJECT-TYPE
			SYNTAX	INTEGER
			MAX-ACCESS	read-only
			STATUS	current
			::= { hmWanMbus15 92 }

hmWanMbus15Value2B		OBJECT-TYPE
			SYNTAX	INTEGER
			MAX-ACCESS	read-only
			STATUS	current
			::= { hmWanMbus15 93 }

hmWanMbus15VIF2C		OBJECT-TYPE
			SYNTAX	INTEGER
			MAX-ACCESS	read-only
			STATUS	current
			::= { hmWanMbus15 94 }

hmWanMbus15Value2C		OBJECT-TYPE
			SYNTAX	INTEGER
			MAX-ACCESS	read-only
			STATUS	current
			::= { hmWanMbus15 95 }

hmWanMbus15VIF2D		OBJECT-TYPE
			SYNTAX	INTEGER
			MAX-ACCESS	read-only
			STATUS	current
			::= { hmWanMbus15 96 }

hmWanMbus15Value2D		OBJECT-TYPE
			SYNTAX	INTEGER
			MAX-ACCESS	read-only
			STATUS	current
			::= { hmWanMbus15 97 }

hmWanMbus15VIF2E		OBJECT-TYPE
			SYNTAX	INTEGER
			MAX-ACCESS	read-only
			STATUS	current
			::= { hmWanMbus15 98 }

hmWanMbus15Value2E		OBJECT-TYPE
			SYNTAX	INTEGER
			MAX-ACCESS	read-only
			STATUS	current
			::= { hmWanMbus15 99 }

hmWanMbus15VIF2F		OBJECT-TYPE
			SYNTAX	INTEGER
			MAX-ACCESS	read-only
			STATUS	current
			::= { hmWanMbus15 100 }

hmWanMbus15Value2F		OBJECT-TYPE
			SYNTAX	INTEGER
			MAX-ACCESS	read-only
			STATUS	current
			::= { hmWanMbus15 101 }

hmWanMbus16			OBJECT IDENTIFIER ::= { hmWanMbus 22 }

hmWanMbus16IdNumber		OBJECT-TYPE
			SYNTAX	Gauge32
			MAX-ACCESS	read-only
			STATUS	current
			::= { hmWanMbus16 1 }

hmWanMbus16Manufacturer	OBJECT-TYPE
			SYNTAX	Gauge32
			MAX-ACCESS	read-only
			STATUS	current
			::= { hmWanMbus16 2 }

hmWanMbus16Version		OBJECT-TYPE
			SYNTAX	Gauge32
			MAX-ACCESS	read-only
			STATUS	current
			::= { hmWanMbus16 3 }

hmWanMbus16Medium		OBJECT-TYPE
			SYNTAX	Gauge32
			MAX-ACCESS	read-only
			STATUS	current
			::= { hmWanMbus16 4 }

hmWanMbus16Status		OBJECT-TYPE
			SYNTAX	Gauge32
			MAX-ACCESS	read-only
			STATUS	current
			::= { hmWanMbus16 5 }

hmWanMbus16VIF00		OBJECT-TYPE
			SYNTAX	INTEGER
			MAX-ACCESS	read-only
			STATUS	current
			::= { hmWanMbus16 6 }

hmWanMbus16Value00		OBJECT-TYPE
			SYNTAX	INTEGER
			MAX-ACCESS	read-only
			STATUS	current
			::= { hmWanMbus16 7 }

hmWanMbus16VIF01		OBJECT-TYPE
			SYNTAX	INTEGER
			MAX-ACCESS	read-only
			STATUS	current
			::= { hmWanMbus16 8 }

hmWanMbus16Value01		OBJECT-TYPE
			SYNTAX	INTEGER
			MAX-ACCESS	read-only
			STATUS	current
			::= { hmWanMbus16 9 }

hmWanMbus16VIF02		OBJECT-TYPE
			SYNTAX	INTEGER
			MAX-ACCESS	read-only
			STATUS	current
			::= { hmWanMbus16 10 }

hmWanMbus16Value02		OBJECT-TYPE
			SYNTAX	INTEGER
			MAX-ACCESS	read-only
			STATUS	current
			::= { hmWanMbus16 11 }

hmWanMbus16VIF03		OBJECT-TYPE
			SYNTAX	INTEGER
			MAX-ACCESS	read-only
			STATUS	current
			::= { hmWanMbus16 12 }

hmWanMbus16Value03		OBJECT-TYPE
			SYNTAX	INTEGER
			MAX-ACCESS	read-only
			STATUS	current
			::= { hmWanMbus16 13 }

hmWanMbus16VIF04		OBJECT-TYPE
			SYNTAX	INTEGER
			MAX-ACCESS	read-only
			STATUS	current
			::= { hmWanMbus16 14 }

hmWanMbus16Value04		OBJECT-TYPE
			SYNTAX	INTEGER
			MAX-ACCESS	read-only
			STATUS	current
			::= { hmWanMbus16 15 }

hmWanMbus16VIF05		OBJECT-TYPE
			SYNTAX	INTEGER
			MAX-ACCESS	read-only
			STATUS	current
			::= { hmWanMbus16 16 }

hmWanMbus16Value05		OBJECT-TYPE
			SYNTAX	INTEGER
			MAX-ACCESS	read-only
			STATUS	current
			::= { hmWanMbus16 17 }

hmWanMbus16VIF06		OBJECT-TYPE
			SYNTAX	INTEGER
			MAX-ACCESS	read-only
			STATUS	current
			::= { hmWanMbus16 18 }

hmWanMbus16Value06		OBJECT-TYPE
			SYNTAX	INTEGER
			MAX-ACCESS	read-only
			STATUS	current
			::= { hmWanMbus16 19 }

hmWanMbus16VIF07		OBJECT-TYPE
			SYNTAX	INTEGER
			MAX-ACCESS	read-only
			STATUS	current
			::= { hmWanMbus16 20 }

hmWanMbus16Value07		OBJECT-TYPE
			SYNTAX	INTEGER
			MAX-ACCESS	read-only
			STATUS	current
			::= { hmWanMbus16 21 }

hmWanMbus16VIF08		OBJECT-TYPE
			SYNTAX	INTEGER
			MAX-ACCESS	read-only
			STATUS	current
			::= { hmWanMbus16 22 }

hmWanMbus16Value08		OBJECT-TYPE
			SYNTAX	INTEGER
			MAX-ACCESS	read-only
			STATUS	current
			::= { hmWanMbus16 23 }

hmWanMbus16VIF09		OBJECT-TYPE
			SYNTAX	INTEGER
			MAX-ACCESS	read-only
			STATUS	current
			::= { hmWanMbus16 24 }

hmWanMbus16Value09		OBJECT-TYPE
			SYNTAX	INTEGER
			MAX-ACCESS	read-only
			STATUS	current
			::= { hmWanMbus16 25 }

hmWanMbus16VIF0A		OBJECT-TYPE
			SYNTAX	INTEGER
			MAX-ACCESS	read-only
			STATUS	current
			::= { hmWanMbus16 26 }

hmWanMbus16Value0A		OBJECT-TYPE
			SYNTAX	INTEGER
			MAX-ACCESS	read-only
			STATUS	current
			::= { hmWanMbus16 27 }

hmWanMbus16VIF0B		OBJECT-TYPE
			SYNTAX	INTEGER
			MAX-ACCESS	read-only
			STATUS	current
			::= { hmWanMbus16 28 }

hmWanMbus16Value0B		OBJECT-TYPE
			SYNTAX	INTEGER
			MAX-ACCESS	read-only
			STATUS	current
			::= { hmWanMbus16 29 }

hmWanMbus16VIF0C		OBJECT-TYPE
			SYNTAX	INTEGER
			MAX-ACCESS	read-only
			STATUS	current
			::= { hmWanMbus16 30 }

hmWanMbus16Value0C		OBJECT-TYPE
			SYNTAX	INTEGER
			MAX-ACCESS	read-only
			STATUS	current
			::= { hmWanMbus16 31 }

hmWanMbus16VIF0D		OBJECT-TYPE
			SYNTAX	INTEGER
			MAX-ACCESS	read-only
			STATUS	current
			::= { hmWanMbus16 32 }

hmWanMbus16Value0D		OBJECT-TYPE
			SYNTAX	INTEGER
			MAX-ACCESS	read-only
			STATUS	current
			::= { hmWanMbus16 33 }

hmWanMbus16VIF0E		OBJECT-TYPE
			SYNTAX	INTEGER
			MAX-ACCESS	read-only
			STATUS	current
			::= { hmWanMbus16 34 }

hmWanMbus16Value0E		OBJECT-TYPE
			SYNTAX	INTEGER
			MAX-ACCESS	read-only
			STATUS	current
			::= { hmWanMbus16 35 }

hmWanMbus16VIF0F		OBJECT-TYPE
			SYNTAX	INTEGER
			MAX-ACCESS	read-only
			STATUS	current
			::= { hmWanMbus16 36 }

hmWanMbus16Value0F		OBJECT-TYPE
			SYNTAX	INTEGER
			MAX-ACCESS	read-only
			STATUS	current
			::= { hmWanMbus16 37 }

hmWanMbus16VIF10		OBJECT-TYPE
			SYNTAX	INTEGER
			MAX-ACCESS	read-only
			STATUS	current
			::= { hmWanMbus16 38 }

hmWanMbus16Value10		OBJECT-TYPE
			SYNTAX	INTEGER
			MAX-ACCESS	read-only
			STATUS	current
			::= { hmWanMbus16 39 }

hmWanMbus16VIF11		OBJECT-TYPE
			SYNTAX	INTEGER
			MAX-ACCESS	read-only
			STATUS	current
			::= { hmWanMbus16 40 }

hmWanMbus16Value11		OBJECT-TYPE
			SYNTAX	INTEGER
			MAX-ACCESS	read-only
			STATUS	current
			::= { hmWanMbus16 41 }

hmWanMbus16VIF12		OBJECT-TYPE
			SYNTAX	INTEGER
			MAX-ACCESS	read-only
			STATUS	current
			::= { hmWanMbus16 42 }

hmWanMbus16Value12		OBJECT-TYPE
			SYNTAX	INTEGER
			MAX-ACCESS	read-only
			STATUS	current
			::= { hmWanMbus16 43 }

hmWanMbus16VIF13		OBJECT-TYPE
			SYNTAX	INTEGER
			MAX-ACCESS	read-only
			STATUS	current
			::= { hmWanMbus16 44 }

hmWanMbus16Value13		OBJECT-TYPE
			SYNTAX	INTEGER
			MAX-ACCESS	read-only
			STATUS	current
			::= { hmWanMbus16 45 }

hmWanMbus16VIF14		OBJECT-TYPE
			SYNTAX	INTEGER
			MAX-ACCESS	read-only
			STATUS	current
			::= { hmWanMbus16 46 }

hmWanMbus16Value14		OBJECT-TYPE
			SYNTAX	INTEGER
			MAX-ACCESS	read-only
			STATUS	current
			::= { hmWanMbus16 47 }

hmWanMbus16VIF15		OBJECT-TYPE
			SYNTAX	INTEGER
			MAX-ACCESS	read-only
			STATUS	current
			::= { hmWanMbus16 48 }

hmWanMbus16Value15		OBJECT-TYPE
			SYNTAX	INTEGER
			MAX-ACCESS	read-only
			STATUS	current
			::= { hmWanMbus16 49 }

hmWanMbus16VIF16		OBJECT-TYPE
			SYNTAX	INTEGER
			MAX-ACCESS	read-only
			STATUS	current
			::= { hmWanMbus16 50 }

hmWanMbus16Value16		OBJECT-TYPE
			SYNTAX	INTEGER
			MAX-ACCESS	read-only
			STATUS	current
			::= { hmWanMbus16 51 }

hmWanMbus16VIF17		OBJECT-TYPE
			SYNTAX	INTEGER
			MAX-ACCESS	read-only
			STATUS	current
			::= { hmWanMbus16 52 }

hmWanMbus16Value17		OBJECT-TYPE
			SYNTAX	INTEGER
			MAX-ACCESS	read-only
			STATUS	current
			::= { hmWanMbus16 53 }

hmWanMbus16VIF18		OBJECT-TYPE
			SYNTAX	INTEGER
			MAX-ACCESS	read-only
			STATUS	current
			::= { hmWanMbus16 54 }

hmWanMbus16Value18		OBJECT-TYPE
			SYNTAX	INTEGER
			MAX-ACCESS	read-only
			STATUS	current
			::= { hmWanMbus16 55 }

hmWanMbus16VIF19		OBJECT-TYPE
			SYNTAX	INTEGER
			MAX-ACCESS	read-only
			STATUS	current
			::= { hmWanMbus16 56 }

hmWanMbus16Value19		OBJECT-TYPE
			SYNTAX	INTEGER
			MAX-ACCESS	read-only
			STATUS	current
			::= { hmWanMbus16 57 }

hmWanMbus16VIF1A		OBJECT-TYPE
			SYNTAX	INTEGER
			MAX-ACCESS	read-only
			STATUS	current
			::= { hmWanMbus16 58 }

hmWanMbus16Value1A		OBJECT-TYPE
			SYNTAX	INTEGER
			MAX-ACCESS	read-only
			STATUS	current
			::= { hmWanMbus16 59 }

hmWanMbus16VIF1B		OBJECT-TYPE
			SYNTAX	INTEGER
			MAX-ACCESS	read-only
			STATUS	current
			::= { hmWanMbus16 60 }

hmWanMbus16Value1B		OBJECT-TYPE
			SYNTAX	INTEGER
			MAX-ACCESS	read-only
			STATUS	current
			::= { hmWanMbus16 61 }

hmWanMbus16VIF1C		OBJECT-TYPE
			SYNTAX	INTEGER
			MAX-ACCESS	read-only
			STATUS	current
			::= { hmWanMbus16 62 }

hmWanMbus16Value1C		OBJECT-TYPE
			SYNTAX	INTEGER
			MAX-ACCESS	read-only
			STATUS	current
			::= { hmWanMbus16 63 }

hmWanMbus16VIF1D		OBJECT-TYPE
			SYNTAX	INTEGER
			MAX-ACCESS	read-only
			STATUS	current
			::= { hmWanMbus16 64 }

hmWanMbus16Value1D		OBJECT-TYPE
			SYNTAX	INTEGER
			MAX-ACCESS	read-only
			STATUS	current
			::= { hmWanMbus16 65 }

hmWanMbus16VIF1E		OBJECT-TYPE
			SYNTAX	INTEGER
			MAX-ACCESS	read-only
			STATUS	current
			::= { hmWanMbus16 66 }

hmWanMbus16Value1E		OBJECT-TYPE
			SYNTAX	INTEGER
			MAX-ACCESS	read-only
			STATUS	current
			::= { hmWanMbus16 67 }

hmWanMbus16VIF1F		OBJECT-TYPE
			SYNTAX	INTEGER
			MAX-ACCESS	read-only
			STATUS	current
			::= { hmWanMbus16 68 }

hmWanMbus16Value1F		OBJECT-TYPE
			SYNTAX	INTEGER
			MAX-ACCESS	read-only
			STATUS	current
			::= { hmWanMbus16 69 }

hmWanMbus16VIF20		OBJECT-TYPE
			SYNTAX	INTEGER
			MAX-ACCESS	read-only
			STATUS	current
			::= { hmWanMbus16 70 }

hmWanMbus16Value20		OBJECT-TYPE
			SYNTAX	INTEGER
			MAX-ACCESS	read-only
			STATUS	current
			::= { hmWanMbus16 71 }

hmWanMbus16VIF21		OBJECT-TYPE
			SYNTAX	INTEGER
			MAX-ACCESS	read-only
			STATUS	current
			::= { hmWanMbus16 72 }

hmWanMbus16Value21		OBJECT-TYPE
			SYNTAX	INTEGER
			MAX-ACCESS	read-only
			STATUS	current
			::= { hmWanMbus16 73 }

hmWanMbus16VIF22		OBJECT-TYPE
			SYNTAX	INTEGER
			MAX-ACCESS	read-only
			STATUS	current
			::= { hmWanMbus16 74 }

hmWanMbus16Value22		OBJECT-TYPE
			SYNTAX	INTEGER
			MAX-ACCESS	read-only
			STATUS	current
			::= { hmWanMbus16 75 }

hmWanMbus16VIF23		OBJECT-TYPE
			SYNTAX	INTEGER
			MAX-ACCESS	read-only
			STATUS	current
			::= { hmWanMbus16 76 }

hmWanMbus16Value23		OBJECT-TYPE
			SYNTAX	INTEGER
			MAX-ACCESS	read-only
			STATUS	current
			::= { hmWanMbus16 77 }

hmWanMbus16VIF24		OBJECT-TYPE
			SYNTAX	INTEGER
			MAX-ACCESS	read-only
			STATUS	current
			::= { hmWanMbus16 78 }

hmWanMbus16Value24		OBJECT-TYPE
			SYNTAX	INTEGER
			MAX-ACCESS	read-only
			STATUS	current
			::= { hmWanMbus16 79 }

hmWanMbus16VIF25		OBJECT-TYPE
			SYNTAX	INTEGER
			MAX-ACCESS	read-only
			STATUS	current
			::= { hmWanMbus16 80 }

hmWanMbus16Value25		OBJECT-TYPE
			SYNTAX	INTEGER
			MAX-ACCESS	read-only
			STATUS	current
			::= { hmWanMbus16 81 }

hmWanMbus16VIF26		OBJECT-TYPE
			SYNTAX	INTEGER
			MAX-ACCESS	read-only
			STATUS	current
			::= { hmWanMbus16 82 }

hmWanMbus16Value26		OBJECT-TYPE
			SYNTAX	INTEGER
			MAX-ACCESS	read-only
			STATUS	current
			::= { hmWanMbus16 83 }

hmWanMbus16VIF27		OBJECT-TYPE
			SYNTAX	INTEGER
			MAX-ACCESS	read-only
			STATUS	current
			::= { hmWanMbus16 84 }

hmWanMbus16Value27		OBJECT-TYPE
			SYNTAX	INTEGER
			MAX-ACCESS	read-only
			STATUS	current
			::= { hmWanMbus16 85 }

hmWanMbus16VIF28		OBJECT-TYPE
			SYNTAX	INTEGER
			MAX-ACCESS	read-only
			STATUS	current
			::= { hmWanMbus16 86 }

hmWanMbus16Value28		OBJECT-TYPE
			SYNTAX	INTEGER
			MAX-ACCESS	read-only
			STATUS	current
			::= { hmWanMbus16 87 }

hmWanMbus16VIF29		OBJECT-TYPE
			SYNTAX	INTEGER
			MAX-ACCESS	read-only
			STATUS	current
			::= { hmWanMbus16 88 }

hmWanMbus16Value29		OBJECT-TYPE
			SYNTAX	INTEGER
			MAX-ACCESS	read-only
			STATUS	current
			::= { hmWanMbus16 89 }

hmWanMbus16VIF2A		OBJECT-TYPE
			SYNTAX	INTEGER
			MAX-ACCESS	read-only
			STATUS	current
			::= { hmWanMbus16 90 }

hmWanMbus16Value2A		OBJECT-TYPE
			SYNTAX	INTEGER
			MAX-ACCESS	read-only
			STATUS	current
			::= { hmWanMbus16 91 }

hmWanMbus16VIF2B		OBJECT-TYPE
			SYNTAX	INTEGER
			MAX-ACCESS	read-only
			STATUS	current
			::= { hmWanMbus16 92 }

hmWanMbus16Value2B		OBJECT-TYPE
			SYNTAX	INTEGER
			MAX-ACCESS	read-only
			STATUS	current
			::= { hmWanMbus16 93 }

hmWanMbus16VIF2C		OBJECT-TYPE
			SYNTAX	INTEGER
			MAX-ACCESS	read-only
			STATUS	current
			::= { hmWanMbus16 94 }

hmWanMbus16Value2C		OBJECT-TYPE
			SYNTAX	INTEGER
			MAX-ACCESS	read-only
			STATUS	current
			::= { hmWanMbus16 95 }

hmWanMbus16VIF2D		OBJECT-TYPE
			SYNTAX	INTEGER
			MAX-ACCESS	read-only
			STATUS	current
			::= { hmWanMbus16 96 }

hmWanMbus16Value2D		OBJECT-TYPE
			SYNTAX	INTEGER
			MAX-ACCESS	read-only
			STATUS	current
			::= { hmWanMbus16 97 }

hmWanMbus16VIF2E		OBJECT-TYPE
			SYNTAX	INTEGER
			MAX-ACCESS	read-only
			STATUS	current
			::= { hmWanMbus16 98 }

hmWanMbus16Value2E		OBJECT-TYPE
			SYNTAX	INTEGER
			MAX-ACCESS	read-only
			STATUS	current
			::= { hmWanMbus16 99 }

hmWanMbus16VIF2F		OBJECT-TYPE
			SYNTAX	INTEGER
			MAX-ACCESS	read-only
			STATUS	current
			::= { hmWanMbus16 100 }

hmWanMbus16Value2F		OBJECT-TYPE
			SYNTAX	INTEGER
			MAX-ACCESS	read-only
			STATUS	current
			::= { hmWanMbus16 101 }

hmWanMbus17			OBJECT IDENTIFIER ::= { hmWanMbus 23 }

hmWanMbus17IdNumber		OBJECT-TYPE
			SYNTAX	Gauge32
			MAX-ACCESS	read-only
			STATUS	current
			::= { hmWanMbus17 1 }

hmWanMbus17Manufacturer	OBJECT-TYPE
			SYNTAX	Gauge32
			MAX-ACCESS	read-only
			STATUS	current
			::= { hmWanMbus17 2 }

hmWanMbus17Version		OBJECT-TYPE
			SYNTAX	Gauge32
			MAX-ACCESS	read-only
			STATUS	current
			::= { hmWanMbus17 3 }

hmWanMbus17Medium		OBJECT-TYPE
			SYNTAX	Gauge32
			MAX-ACCESS	read-only
			STATUS	current
			::= { hmWanMbus17 4 }

hmWanMbus17Status		OBJECT-TYPE
			SYNTAX	Gauge32
			MAX-ACCESS	read-only
			STATUS	current
			::= { hmWanMbus17 5 }

hmWanMbus17VIF00		OBJECT-TYPE
			SYNTAX	INTEGER
			MAX-ACCESS	read-only
			STATUS	current
			::= { hmWanMbus17 6 }

hmWanMbus17Value00		OBJECT-TYPE
			SYNTAX	INTEGER
			MAX-ACCESS	read-only
			STATUS	current
			::= { hmWanMbus17 7 }

hmWanMbus17VIF01		OBJECT-TYPE
			SYNTAX	INTEGER
			MAX-ACCESS	read-only
			STATUS	current
			::= { hmWanMbus17 8 }

hmWanMbus17Value01		OBJECT-TYPE
			SYNTAX	INTEGER
			MAX-ACCESS	read-only
			STATUS	current
			::= { hmWanMbus17 9 }

hmWanMbus17VIF02		OBJECT-TYPE
			SYNTAX	INTEGER
			MAX-ACCESS	read-only
			STATUS	current
			::= { hmWanMbus17 10 }

hmWanMbus17Value02		OBJECT-TYPE
			SYNTAX	INTEGER
			MAX-ACCESS	read-only
			STATUS	current
			::= { hmWanMbus17 11 }

hmWanMbus17VIF03		OBJECT-TYPE
			SYNTAX	INTEGER
			MAX-ACCESS	read-only
			STATUS	current
			::= { hmWanMbus17 12 }

hmWanMbus17Value03		OBJECT-TYPE
			SYNTAX	INTEGER
			MAX-ACCESS	read-only
			STATUS	current
			::= { hmWanMbus17 13 }

hmWanMbus17VIF04		OBJECT-TYPE
			SYNTAX	INTEGER
			MAX-ACCESS	read-only
			STATUS	current
			::= { hmWanMbus17 14 }

hmWanMbus17Value04		OBJECT-TYPE
			SYNTAX	INTEGER
			MAX-ACCESS	read-only
			STATUS	current
			::= { hmWanMbus17 15 }

hmWanMbus17VIF05		OBJECT-TYPE
			SYNTAX	INTEGER
			MAX-ACCESS	read-only
			STATUS	current
			::= { hmWanMbus17 16 }

hmWanMbus17Value05		OBJECT-TYPE
			SYNTAX	INTEGER
			MAX-ACCESS	read-only
			STATUS	current
			::= { hmWanMbus17 17 }

hmWanMbus17VIF06		OBJECT-TYPE
			SYNTAX	INTEGER
			MAX-ACCESS	read-only
			STATUS	current
			::= { hmWanMbus17 18 }

hmWanMbus17Value06		OBJECT-TYPE
			SYNTAX	INTEGER
			MAX-ACCESS	read-only
			STATUS	current
			::= { hmWanMbus17 19 }

hmWanMbus17VIF07		OBJECT-TYPE
			SYNTAX	INTEGER
			MAX-ACCESS	read-only
			STATUS	current
			::= { hmWanMbus17 20 }

hmWanMbus17Value07		OBJECT-TYPE
			SYNTAX	INTEGER
			MAX-ACCESS	read-only
			STATUS	current
			::= { hmWanMbus17 21 }

hmWanMbus17VIF08		OBJECT-TYPE
			SYNTAX	INTEGER
			MAX-ACCESS	read-only
			STATUS	current
			::= { hmWanMbus17 22 }

hmWanMbus17Value08		OBJECT-TYPE
			SYNTAX	INTEGER
			MAX-ACCESS	read-only
			STATUS	current
			::= { hmWanMbus17 23 }

hmWanMbus17VIF09		OBJECT-TYPE
			SYNTAX	INTEGER
			MAX-ACCESS	read-only
			STATUS	current
			::= { hmWanMbus17 24 }

hmWanMbus17Value09		OBJECT-TYPE
			SYNTAX	INTEGER
			MAX-ACCESS	read-only
			STATUS	current
			::= { hmWanMbus17 25 }

hmWanMbus17VIF0A		OBJECT-TYPE
			SYNTAX	INTEGER
			MAX-ACCESS	read-only
			STATUS	current
			::= { hmWanMbus17 26 }

hmWanMbus17Value0A		OBJECT-TYPE
			SYNTAX	INTEGER
			MAX-ACCESS	read-only
			STATUS	current
			::= { hmWanMbus17 27 }

hmWanMbus17VIF0B		OBJECT-TYPE
			SYNTAX	INTEGER
			MAX-ACCESS	read-only
			STATUS	current
			::= { hmWanMbus17 28 }

hmWanMbus17Value0B		OBJECT-TYPE
			SYNTAX	INTEGER
			MAX-ACCESS	read-only
			STATUS	current
			::= { hmWanMbus17 29 }

hmWanMbus17VIF0C		OBJECT-TYPE
			SYNTAX	INTEGER
			MAX-ACCESS	read-only
			STATUS	current
			::= { hmWanMbus17 30 }

hmWanMbus17Value0C		OBJECT-TYPE
			SYNTAX	INTEGER
			MAX-ACCESS	read-only
			STATUS	current
			::= { hmWanMbus17 31 }

hmWanMbus17VIF0D		OBJECT-TYPE
			SYNTAX	INTEGER
			MAX-ACCESS	read-only
			STATUS	current
			::= { hmWanMbus17 32 }

hmWanMbus17Value0D		OBJECT-TYPE
			SYNTAX	INTEGER
			MAX-ACCESS	read-only
			STATUS	current
			::= { hmWanMbus17 33 }

hmWanMbus17VIF0E		OBJECT-TYPE
			SYNTAX	INTEGER
			MAX-ACCESS	read-only
			STATUS	current
			::= { hmWanMbus17 34 }

hmWanMbus17Value0E		OBJECT-TYPE
			SYNTAX	INTEGER
			MAX-ACCESS	read-only
			STATUS	current
			::= { hmWanMbus17 35 }

hmWanMbus17VIF0F		OBJECT-TYPE
			SYNTAX	INTEGER
			MAX-ACCESS	read-only
			STATUS	current
			::= { hmWanMbus17 36 }

hmWanMbus17Value0F		OBJECT-TYPE
			SYNTAX	INTEGER
			MAX-ACCESS	read-only
			STATUS	current
			::= { hmWanMbus17 37 }

hmWanMbus17VIF10		OBJECT-TYPE
			SYNTAX	INTEGER
			MAX-ACCESS	read-only
			STATUS	current
			::= { hmWanMbus17 38 }

hmWanMbus17Value10		OBJECT-TYPE
			SYNTAX	INTEGER
			MAX-ACCESS	read-only
			STATUS	current
			::= { hmWanMbus17 39 }

hmWanMbus17VIF11		OBJECT-TYPE
			SYNTAX	INTEGER
			MAX-ACCESS	read-only
			STATUS	current
			::= { hmWanMbus17 40 }

hmWanMbus17Value11		OBJECT-TYPE
			SYNTAX	INTEGER
			MAX-ACCESS	read-only
			STATUS	current
			::= { hmWanMbus17 41 }

hmWanMbus17VIF12		OBJECT-TYPE
			SYNTAX	INTEGER
			MAX-ACCESS	read-only
			STATUS	current
			::= { hmWanMbus17 42 }

hmWanMbus17Value12		OBJECT-TYPE
			SYNTAX	INTEGER
			MAX-ACCESS	read-only
			STATUS	current
			::= { hmWanMbus17 43 }

hmWanMbus17VIF13		OBJECT-TYPE
			SYNTAX	INTEGER
			MAX-ACCESS	read-only
			STATUS	current
			::= { hmWanMbus17 44 }

hmWanMbus17Value13		OBJECT-TYPE
			SYNTAX	INTEGER
			MAX-ACCESS	read-only
			STATUS	current
			::= { hmWanMbus17 45 }

hmWanMbus17VIF14		OBJECT-TYPE
			SYNTAX	INTEGER
			MAX-ACCESS	read-only
			STATUS	current
			::= { hmWanMbus17 46 }

hmWanMbus17Value14		OBJECT-TYPE
			SYNTAX	INTEGER
			MAX-ACCESS	read-only
			STATUS	current
			::= { hmWanMbus17 47 }

hmWanMbus17VIF15		OBJECT-TYPE
			SYNTAX	INTEGER
			MAX-ACCESS	read-only
			STATUS	current
			::= { hmWanMbus17 48 }

hmWanMbus17Value15		OBJECT-TYPE
			SYNTAX	INTEGER
			MAX-ACCESS	read-only
			STATUS	current
			::= { hmWanMbus17 49 }

hmWanMbus17VIF16		OBJECT-TYPE
			SYNTAX	INTEGER
			MAX-ACCESS	read-only
			STATUS	current
			::= { hmWanMbus17 50 }

hmWanMbus17Value16		OBJECT-TYPE
			SYNTAX	INTEGER
			MAX-ACCESS	read-only
			STATUS	current
			::= { hmWanMbus17 51 }

hmWanMbus17VIF17		OBJECT-TYPE
			SYNTAX	INTEGER
			MAX-ACCESS	read-only
			STATUS	current
			::= { hmWanMbus17 52 }

hmWanMbus17Value17		OBJECT-TYPE
			SYNTAX	INTEGER
			MAX-ACCESS	read-only
			STATUS	current
			::= { hmWanMbus17 53 }

hmWanMbus17VIF18		OBJECT-TYPE
			SYNTAX	INTEGER
			MAX-ACCESS	read-only
			STATUS	current
			::= { hmWanMbus17 54 }

hmWanMbus17Value18		OBJECT-TYPE
			SYNTAX	INTEGER
			MAX-ACCESS	read-only
			STATUS	current
			::= { hmWanMbus17 55 }

hmWanMbus17VIF19		OBJECT-TYPE
			SYNTAX	INTEGER
			MAX-ACCESS	read-only
			STATUS	current
			::= { hmWanMbus17 56 }

hmWanMbus17Value19		OBJECT-TYPE
			SYNTAX	INTEGER
			MAX-ACCESS	read-only
			STATUS	current
			::= { hmWanMbus17 57 }

hmWanMbus17VIF1A		OBJECT-TYPE
			SYNTAX	INTEGER
			MAX-ACCESS	read-only
			STATUS	current
			::= { hmWanMbus17 58 }

hmWanMbus17Value1A		OBJECT-TYPE
			SYNTAX	INTEGER
			MAX-ACCESS	read-only
			STATUS	current
			::= { hmWanMbus17 59 }

hmWanMbus17VIF1B		OBJECT-TYPE
			SYNTAX	INTEGER
			MAX-ACCESS	read-only
			STATUS	current
			::= { hmWanMbus17 60 }

hmWanMbus17Value1B		OBJECT-TYPE
			SYNTAX	INTEGER
			MAX-ACCESS	read-only
			STATUS	current
			::= { hmWanMbus17 61 }

hmWanMbus17VIF1C		OBJECT-TYPE
			SYNTAX	INTEGER
			MAX-ACCESS	read-only
			STATUS	current
			::= { hmWanMbus17 62 }

hmWanMbus17Value1C		OBJECT-TYPE
			SYNTAX	INTEGER
			MAX-ACCESS	read-only
			STATUS	current
			::= { hmWanMbus17 63 }

hmWanMbus17VIF1D		OBJECT-TYPE
			SYNTAX	INTEGER
			MAX-ACCESS	read-only
			STATUS	current
			::= { hmWanMbus17 64 }

hmWanMbus17Value1D		OBJECT-TYPE
			SYNTAX	INTEGER
			MAX-ACCESS	read-only
			STATUS	current
			::= { hmWanMbus17 65 }

hmWanMbus17VIF1E		OBJECT-TYPE
			SYNTAX	INTEGER
			MAX-ACCESS	read-only
			STATUS	current
			::= { hmWanMbus17 66 }

hmWanMbus17Value1E		OBJECT-TYPE
			SYNTAX	INTEGER
			MAX-ACCESS	read-only
			STATUS	current
			::= { hmWanMbus17 67 }

hmWanMbus17VIF1F		OBJECT-TYPE
			SYNTAX	INTEGER
			MAX-ACCESS	read-only
			STATUS	current
			::= { hmWanMbus17 68 }

hmWanMbus17Value1F		OBJECT-TYPE
			SYNTAX	INTEGER
			MAX-ACCESS	read-only
			STATUS	current
			::= { hmWanMbus17 69 }

hmWanMbus17VIF20		OBJECT-TYPE
			SYNTAX	INTEGER
			MAX-ACCESS	read-only
			STATUS	current
			::= { hmWanMbus17 70 }

hmWanMbus17Value20		OBJECT-TYPE
			SYNTAX	INTEGER
			MAX-ACCESS	read-only
			STATUS	current
			::= { hmWanMbus17 71 }

hmWanMbus17VIF21		OBJECT-TYPE
			SYNTAX	INTEGER
			MAX-ACCESS	read-only
			STATUS	current
			::= { hmWanMbus17 72 }

hmWanMbus17Value21		OBJECT-TYPE
			SYNTAX	INTEGER
			MAX-ACCESS	read-only
			STATUS	current
			::= { hmWanMbus17 73 }

hmWanMbus17VIF22		OBJECT-TYPE
			SYNTAX	INTEGER
			MAX-ACCESS	read-only
			STATUS	current
			::= { hmWanMbus17 74 }

hmWanMbus17Value22		OBJECT-TYPE
			SYNTAX	INTEGER
			MAX-ACCESS	read-only
			STATUS	current
			::= { hmWanMbus17 75 }

hmWanMbus17VIF23		OBJECT-TYPE
			SYNTAX	INTEGER
			MAX-ACCESS	read-only
			STATUS	current
			::= { hmWanMbus17 76 }

hmWanMbus17Value23		OBJECT-TYPE
			SYNTAX	INTEGER
			MAX-ACCESS	read-only
			STATUS	current
			::= { hmWanMbus17 77 }

hmWanMbus17VIF24		OBJECT-TYPE
			SYNTAX	INTEGER
			MAX-ACCESS	read-only
			STATUS	current
			::= { hmWanMbus17 78 }

hmWanMbus17Value24		OBJECT-TYPE
			SYNTAX	INTEGER
			MAX-ACCESS	read-only
			STATUS	current
			::= { hmWanMbus17 79 }

hmWanMbus17VIF25		OBJECT-TYPE
			SYNTAX	INTEGER
			MAX-ACCESS	read-only
			STATUS	current
			::= { hmWanMbus17 80 }

hmWanMbus17Value25		OBJECT-TYPE
			SYNTAX	INTEGER
			MAX-ACCESS	read-only
			STATUS	current
			::= { hmWanMbus17 81 }

hmWanMbus17VIF26		OBJECT-TYPE
			SYNTAX	INTEGER
			MAX-ACCESS	read-only
			STATUS	current
			::= { hmWanMbus17 82 }

hmWanMbus17Value26		OBJECT-TYPE
			SYNTAX	INTEGER
			MAX-ACCESS	read-only
			STATUS	current
			::= { hmWanMbus17 83 }

hmWanMbus17VIF27		OBJECT-TYPE
			SYNTAX	INTEGER
			MAX-ACCESS	read-only
			STATUS	current
			::= { hmWanMbus17 84 }

hmWanMbus17Value27		OBJECT-TYPE
			SYNTAX	INTEGER
			MAX-ACCESS	read-only
			STATUS	current
			::= { hmWanMbus17 85 }

hmWanMbus17VIF28		OBJECT-TYPE
			SYNTAX	INTEGER
			MAX-ACCESS	read-only
			STATUS	current
			::= { hmWanMbus17 86 }

hmWanMbus17Value28		OBJECT-TYPE
			SYNTAX	INTEGER
			MAX-ACCESS	read-only
			STATUS	current
			::= { hmWanMbus17 87 }

hmWanMbus17VIF29		OBJECT-TYPE
			SYNTAX	INTEGER
			MAX-ACCESS	read-only
			STATUS	current
			::= { hmWanMbus17 88 }

hmWanMbus17Value29		OBJECT-TYPE
			SYNTAX	INTEGER
			MAX-ACCESS	read-only
			STATUS	current
			::= { hmWanMbus17 89 }

hmWanMbus17VIF2A		OBJECT-TYPE
			SYNTAX	INTEGER
			MAX-ACCESS	read-only
			STATUS	current
			::= { hmWanMbus17 90 }

hmWanMbus17Value2A		OBJECT-TYPE
			SYNTAX	INTEGER
			MAX-ACCESS	read-only
			STATUS	current
			::= { hmWanMbus17 91 }

hmWanMbus17VIF2B		OBJECT-TYPE
			SYNTAX	INTEGER
			MAX-ACCESS	read-only
			STATUS	current
			::= { hmWanMbus17 92 }

hmWanMbus17Value2B		OBJECT-TYPE
			SYNTAX	INTEGER
			MAX-ACCESS	read-only
			STATUS	current
			::= { hmWanMbus17 93 }

hmWanMbus17VIF2C		OBJECT-TYPE
			SYNTAX	INTEGER
			MAX-ACCESS	read-only
			STATUS	current
			::= { hmWanMbus17 94 }

hmWanMbus17Value2C		OBJECT-TYPE
			SYNTAX	INTEGER
			MAX-ACCESS	read-only
			STATUS	current
			::= { hmWanMbus17 95 }

hmWanMbus17VIF2D		OBJECT-TYPE
			SYNTAX	INTEGER
			MAX-ACCESS	read-only
			STATUS	current
			::= { hmWanMbus17 96 }

hmWanMbus17Value2D		OBJECT-TYPE
			SYNTAX	INTEGER
			MAX-ACCESS	read-only
			STATUS	current
			::= { hmWanMbus17 97 }

hmWanMbus17VIF2E		OBJECT-TYPE
			SYNTAX	INTEGER
			MAX-ACCESS	read-only
			STATUS	current
			::= { hmWanMbus17 98 }

hmWanMbus17Value2E		OBJECT-TYPE
			SYNTAX	INTEGER
			MAX-ACCESS	read-only
			STATUS	current
			::= { hmWanMbus17 99 }

hmWanMbus17VIF2F		OBJECT-TYPE
			SYNTAX	INTEGER
			MAX-ACCESS	read-only
			STATUS	current
			::= { hmWanMbus17 100 }

hmWanMbus17Value2F		OBJECT-TYPE
			SYNTAX	INTEGER
			MAX-ACCESS	read-only
			STATUS	current
			::= { hmWanMbus17 101 }

hmWanMbus18			OBJECT IDENTIFIER ::= { hmWanMbus 24 }

hmWanMbus18IdNumber		OBJECT-TYPE
			SYNTAX	Gauge32
			MAX-ACCESS	read-only
			STATUS	current
			::= { hmWanMbus18 1 }

hmWanMbus18Manufacturer	OBJECT-TYPE
			SYNTAX	Gauge32
			MAX-ACCESS	read-only
			STATUS	current
			::= { hmWanMbus18 2 }

hmWanMbus18Version		OBJECT-TYPE
			SYNTAX	Gauge32
			MAX-ACCESS	read-only
			STATUS	current
			::= { hmWanMbus18 3 }

hmWanMbus18Medium		OBJECT-TYPE
			SYNTAX	Gauge32
			MAX-ACCESS	read-only
			STATUS	current
			::= { hmWanMbus18 4 }

hmWanMbus18Status		OBJECT-TYPE
			SYNTAX	Gauge32
			MAX-ACCESS	read-only
			STATUS	current
			::= { hmWanMbus18 5 }

hmWanMbus18VIF00		OBJECT-TYPE
			SYNTAX	INTEGER
			MAX-ACCESS	read-only
			STATUS	current
			::= { hmWanMbus18 6 }

hmWanMbus18Value00		OBJECT-TYPE
			SYNTAX	INTEGER
			MAX-ACCESS	read-only
			STATUS	current
			::= { hmWanMbus18 7 }

hmWanMbus18VIF01		OBJECT-TYPE
			SYNTAX	INTEGER
			MAX-ACCESS	read-only
			STATUS	current
			::= { hmWanMbus18 8 }

hmWanMbus18Value01		OBJECT-TYPE
			SYNTAX	INTEGER
			MAX-ACCESS	read-only
			STATUS	current
			::= { hmWanMbus18 9 }

hmWanMbus18VIF02		OBJECT-TYPE
			SYNTAX	INTEGER
			MAX-ACCESS	read-only
			STATUS	current
			::= { hmWanMbus18 10 }

hmWanMbus18Value02		OBJECT-TYPE
			SYNTAX	INTEGER
			MAX-ACCESS	read-only
			STATUS	current
			::= { hmWanMbus18 11 }

hmWanMbus18VIF03		OBJECT-TYPE
			SYNTAX	INTEGER
			MAX-ACCESS	read-only
			STATUS	current
			::= { hmWanMbus18 12 }

hmWanMbus18Value03		OBJECT-TYPE
			SYNTAX	INTEGER
			MAX-ACCESS	read-only
			STATUS	current
			::= { hmWanMbus18 13 }

hmWanMbus18VIF04		OBJECT-TYPE
			SYNTAX	INTEGER
			MAX-ACCESS	read-only
			STATUS	current
			::= { hmWanMbus18 14 }

hmWanMbus18Value04		OBJECT-TYPE
			SYNTAX	INTEGER
			MAX-ACCESS	read-only
			STATUS	current
			::= { hmWanMbus18 15 }

hmWanMbus18VIF05		OBJECT-TYPE
			SYNTAX	INTEGER
			MAX-ACCESS	read-only
			STATUS	current
			::= { hmWanMbus18 16 }

hmWanMbus18Value05		OBJECT-TYPE
			SYNTAX	INTEGER
			MAX-ACCESS	read-only
			STATUS	current
			::= { hmWanMbus18 17 }

hmWanMbus18VIF06		OBJECT-TYPE
			SYNTAX	INTEGER
			MAX-ACCESS	read-only
			STATUS	current
			::= { hmWanMbus18 18 }

hmWanMbus18Value06		OBJECT-TYPE
			SYNTAX	INTEGER
			MAX-ACCESS	read-only
			STATUS	current
			::= { hmWanMbus18 19 }

hmWanMbus18VIF07		OBJECT-TYPE
			SYNTAX	INTEGER
			MAX-ACCESS	read-only
			STATUS	current
			::= { hmWanMbus18 20 }

hmWanMbus18Value07		OBJECT-TYPE
			SYNTAX	INTEGER
			MAX-ACCESS	read-only
			STATUS	current
			::= { hmWanMbus18 21 }

hmWanMbus18VIF08		OBJECT-TYPE
			SYNTAX	INTEGER
			MAX-ACCESS	read-only
			STATUS	current
			::= { hmWanMbus18 22 }

hmWanMbus18Value08		OBJECT-TYPE
			SYNTAX	INTEGER
			MAX-ACCESS	read-only
			STATUS	current
			::= { hmWanMbus18 23 }

hmWanMbus18VIF09		OBJECT-TYPE
			SYNTAX	INTEGER
			MAX-ACCESS	read-only
			STATUS	current
			::= { hmWanMbus18 24 }

hmWanMbus18Value09		OBJECT-TYPE
			SYNTAX	INTEGER
			MAX-ACCESS	read-only
			STATUS	current
			::= { hmWanMbus18 25 }

hmWanMbus18VIF0A		OBJECT-TYPE
			SYNTAX	INTEGER
			MAX-ACCESS	read-only
			STATUS	current
			::= { hmWanMbus18 26 }

hmWanMbus18Value0A		OBJECT-TYPE
			SYNTAX	INTEGER
			MAX-ACCESS	read-only
			STATUS	current
			::= { hmWanMbus18 27 }

hmWanMbus18VIF0B		OBJECT-TYPE
			SYNTAX	INTEGER
			MAX-ACCESS	read-only
			STATUS	current
			::= { hmWanMbus18 28 }

hmWanMbus18Value0B		OBJECT-TYPE
			SYNTAX	INTEGER
			MAX-ACCESS	read-only
			STATUS	current
			::= { hmWanMbus18 29 }

hmWanMbus18VIF0C		OBJECT-TYPE
			SYNTAX	INTEGER
			MAX-ACCESS	read-only
			STATUS	current
			::= { hmWanMbus18 30 }

hmWanMbus18Value0C		OBJECT-TYPE
			SYNTAX	INTEGER
			MAX-ACCESS	read-only
			STATUS	current
			::= { hmWanMbus18 31 }

hmWanMbus18VIF0D		OBJECT-TYPE
			SYNTAX	INTEGER
			MAX-ACCESS	read-only
			STATUS	current
			::= { hmWanMbus18 32 }

hmWanMbus18Value0D		OBJECT-TYPE
			SYNTAX	INTEGER
			MAX-ACCESS	read-only
			STATUS	current
			::= { hmWanMbus18 33 }

hmWanMbus18VIF0E		OBJECT-TYPE
			SYNTAX	INTEGER
			MAX-ACCESS	read-only
			STATUS	current
			::= { hmWanMbus18 34 }

hmWanMbus18Value0E		OBJECT-TYPE
			SYNTAX	INTEGER
			MAX-ACCESS	read-only
			STATUS	current
			::= { hmWanMbus18 35 }

hmWanMbus18VIF0F		OBJECT-TYPE
			SYNTAX	INTEGER
			MAX-ACCESS	read-only
			STATUS	current
			::= { hmWanMbus18 36 }

hmWanMbus18Value0F		OBJECT-TYPE
			SYNTAX	INTEGER
			MAX-ACCESS	read-only
			STATUS	current
			::= { hmWanMbus18 37 }

hmWanMbus18VIF10		OBJECT-TYPE
			SYNTAX	INTEGER
			MAX-ACCESS	read-only
			STATUS	current
			::= { hmWanMbus18 38 }

hmWanMbus18Value10		OBJECT-TYPE
			SYNTAX	INTEGER
			MAX-ACCESS	read-only
			STATUS	current
			::= { hmWanMbus18 39 }

hmWanMbus18VIF11		OBJECT-TYPE
			SYNTAX	INTEGER
			MAX-ACCESS	read-only
			STATUS	current
			::= { hmWanMbus18 40 }

hmWanMbus18Value11		OBJECT-TYPE
			SYNTAX	INTEGER
			MAX-ACCESS	read-only
			STATUS	current
			::= { hmWanMbus18 41 }

hmWanMbus18VIF12		OBJECT-TYPE
			SYNTAX	INTEGER
			MAX-ACCESS	read-only
			STATUS	current
			::= { hmWanMbus18 42 }

hmWanMbus18Value12		OBJECT-TYPE
			SYNTAX	INTEGER
			MAX-ACCESS	read-only
			STATUS	current
			::= { hmWanMbus18 43 }

hmWanMbus18VIF13		OBJECT-TYPE
			SYNTAX	INTEGER
			MAX-ACCESS	read-only
			STATUS	current
			::= { hmWanMbus18 44 }

hmWanMbus18Value13		OBJECT-TYPE
			SYNTAX	INTEGER
			MAX-ACCESS	read-only
			STATUS	current
			::= { hmWanMbus18 45 }

hmWanMbus18VIF14		OBJECT-TYPE
			SYNTAX	INTEGER
			MAX-ACCESS	read-only
			STATUS	current
			::= { hmWanMbus18 46 }

hmWanMbus18Value14		OBJECT-TYPE
			SYNTAX	INTEGER
			MAX-ACCESS	read-only
			STATUS	current
			::= { hmWanMbus18 47 }

hmWanMbus18VIF15		OBJECT-TYPE
			SYNTAX	INTEGER
			MAX-ACCESS	read-only
			STATUS	current
			::= { hmWanMbus18 48 }

hmWanMbus18Value15		OBJECT-TYPE
			SYNTAX	INTEGER
			MAX-ACCESS	read-only
			STATUS	current
			::= { hmWanMbus18 49 }

hmWanMbus18VIF16		OBJECT-TYPE
			SYNTAX	INTEGER
			MAX-ACCESS	read-only
			STATUS	current
			::= { hmWanMbus18 50 }

hmWanMbus18Value16		OBJECT-TYPE
			SYNTAX	INTEGER
			MAX-ACCESS	read-only
			STATUS	current
			::= { hmWanMbus18 51 }

hmWanMbus18VIF17		OBJECT-TYPE
			SYNTAX	INTEGER
			MAX-ACCESS	read-only
			STATUS	current
			::= { hmWanMbus18 52 }

hmWanMbus18Value17		OBJECT-TYPE
			SYNTAX	INTEGER
			MAX-ACCESS	read-only
			STATUS	current
			::= { hmWanMbus18 53 }

hmWanMbus18VIF18		OBJECT-TYPE
			SYNTAX	INTEGER
			MAX-ACCESS	read-only
			STATUS	current
			::= { hmWanMbus18 54 }

hmWanMbus18Value18		OBJECT-TYPE
			SYNTAX	INTEGER
			MAX-ACCESS	read-only
			STATUS	current
			::= { hmWanMbus18 55 }

hmWanMbus18VIF19		OBJECT-TYPE
			SYNTAX	INTEGER
			MAX-ACCESS	read-only
			STATUS	current
			::= { hmWanMbus18 56 }

hmWanMbus18Value19		OBJECT-TYPE
			SYNTAX	INTEGER
			MAX-ACCESS	read-only
			STATUS	current
			::= { hmWanMbus18 57 }

hmWanMbus18VIF1A		OBJECT-TYPE
			SYNTAX	INTEGER
			MAX-ACCESS	read-only
			STATUS	current
			::= { hmWanMbus18 58 }

hmWanMbus18Value1A		OBJECT-TYPE
			SYNTAX	INTEGER
			MAX-ACCESS	read-only
			STATUS	current
			::= { hmWanMbus18 59 }

hmWanMbus18VIF1B		OBJECT-TYPE
			SYNTAX	INTEGER
			MAX-ACCESS	read-only
			STATUS	current
			::= { hmWanMbus18 60 }

hmWanMbus18Value1B		OBJECT-TYPE
			SYNTAX	INTEGER
			MAX-ACCESS	read-only
			STATUS	current
			::= { hmWanMbus18 61 }

hmWanMbus18VIF1C		OBJECT-TYPE
			SYNTAX	INTEGER
			MAX-ACCESS	read-only
			STATUS	current
			::= { hmWanMbus18 62 }

hmWanMbus18Value1C		OBJECT-TYPE
			SYNTAX	INTEGER
			MAX-ACCESS	read-only
			STATUS	current
			::= { hmWanMbus18 63 }

hmWanMbus18VIF1D		OBJECT-TYPE
			SYNTAX	INTEGER
			MAX-ACCESS	read-only
			STATUS	current
			::= { hmWanMbus18 64 }

hmWanMbus18Value1D		OBJECT-TYPE
			SYNTAX	INTEGER
			MAX-ACCESS	read-only
			STATUS	current
			::= { hmWanMbus18 65 }

hmWanMbus18VIF1E		OBJECT-TYPE
			SYNTAX	INTEGER
			MAX-ACCESS	read-only
			STATUS	current
			::= { hmWanMbus18 66 }

hmWanMbus18Value1E		OBJECT-TYPE
			SYNTAX	INTEGER
			MAX-ACCESS	read-only
			STATUS	current
			::= { hmWanMbus18 67 }

hmWanMbus18VIF1F		OBJECT-TYPE
			SYNTAX	INTEGER
			MAX-ACCESS	read-only
			STATUS	current
			::= { hmWanMbus18 68 }

hmWanMbus18Value1F		OBJECT-TYPE
			SYNTAX	INTEGER
			MAX-ACCESS	read-only
			STATUS	current
			::= { hmWanMbus18 69 }

hmWanMbus18VIF20		OBJECT-TYPE
			SYNTAX	INTEGER
			MAX-ACCESS	read-only
			STATUS	current
			::= { hmWanMbus18 70 }

hmWanMbus18Value20		OBJECT-TYPE
			SYNTAX	INTEGER
			MAX-ACCESS	read-only
			STATUS	current
			::= { hmWanMbus18 71 }

hmWanMbus18VIF21		OBJECT-TYPE
			SYNTAX	INTEGER
			MAX-ACCESS	read-only
			STATUS	current
			::= { hmWanMbus18 72 }

hmWanMbus18Value21		OBJECT-TYPE
			SYNTAX	INTEGER
			MAX-ACCESS	read-only
			STATUS	current
			::= { hmWanMbus18 73 }

hmWanMbus18VIF22		OBJECT-TYPE
			SYNTAX	INTEGER
			MAX-ACCESS	read-only
			STATUS	current
			::= { hmWanMbus18 74 }

hmWanMbus18Value22		OBJECT-TYPE
			SYNTAX	INTEGER
			MAX-ACCESS	read-only
			STATUS	current
			::= { hmWanMbus18 75 }

hmWanMbus18VIF23		OBJECT-TYPE
			SYNTAX	INTEGER
			MAX-ACCESS	read-only
			STATUS	current
			::= { hmWanMbus18 76 }

hmWanMbus18Value23		OBJECT-TYPE
			SYNTAX	INTEGER
			MAX-ACCESS	read-only
			STATUS	current
			::= { hmWanMbus18 77 }

hmWanMbus18VIF24		OBJECT-TYPE
			SYNTAX	INTEGER
			MAX-ACCESS	read-only
			STATUS	current
			::= { hmWanMbus18 78 }

hmWanMbus18Value24		OBJECT-TYPE
			SYNTAX	INTEGER
			MAX-ACCESS	read-only
			STATUS	current
			::= { hmWanMbus18 79 }

hmWanMbus18VIF25		OBJECT-TYPE
			SYNTAX	INTEGER
			MAX-ACCESS	read-only
			STATUS	current
			::= { hmWanMbus18 80 }

hmWanMbus18Value25		OBJECT-TYPE
			SYNTAX	INTEGER
			MAX-ACCESS	read-only
			STATUS	current
			::= { hmWanMbus18 81 }

hmWanMbus18VIF26		OBJECT-TYPE
			SYNTAX	INTEGER
			MAX-ACCESS	read-only
			STATUS	current
			::= { hmWanMbus18 82 }

hmWanMbus18Value26		OBJECT-TYPE
			SYNTAX	INTEGER
			MAX-ACCESS	read-only
			STATUS	current
			::= { hmWanMbus18 83 }

hmWanMbus18VIF27		OBJECT-TYPE
			SYNTAX	INTEGER
			MAX-ACCESS	read-only
			STATUS	current
			::= { hmWanMbus18 84 }

hmWanMbus18Value27		OBJECT-TYPE
			SYNTAX	INTEGER
			MAX-ACCESS	read-only
			STATUS	current
			::= { hmWanMbus18 85 }

hmWanMbus18VIF28		OBJECT-TYPE
			SYNTAX	INTEGER
			MAX-ACCESS	read-only
			STATUS	current
			::= { hmWanMbus18 86 }

hmWanMbus18Value28		OBJECT-TYPE
			SYNTAX	INTEGER
			MAX-ACCESS	read-only
			STATUS	current
			::= { hmWanMbus18 87 }

hmWanMbus18VIF29		OBJECT-TYPE
			SYNTAX	INTEGER
			MAX-ACCESS	read-only
			STATUS	current
			::= { hmWanMbus18 88 }

hmWanMbus18Value29		OBJECT-TYPE
			SYNTAX	INTEGER
			MAX-ACCESS	read-only
			STATUS	current
			::= { hmWanMbus18 89 }

hmWanMbus18VIF2A		OBJECT-TYPE
			SYNTAX	INTEGER
			MAX-ACCESS	read-only
			STATUS	current
			::= { hmWanMbus18 90 }

hmWanMbus18Value2A		OBJECT-TYPE
			SYNTAX	INTEGER
			MAX-ACCESS	read-only
			STATUS	current
			::= { hmWanMbus18 91 }

hmWanMbus18VIF2B		OBJECT-TYPE
			SYNTAX	INTEGER
			MAX-ACCESS	read-only
			STATUS	current
			::= { hmWanMbus18 92 }

hmWanMbus18Value2B		OBJECT-TYPE
			SYNTAX	INTEGER
			MAX-ACCESS	read-only
			STATUS	current
			::= { hmWanMbus18 93 }

hmWanMbus18VIF2C		OBJECT-TYPE
			SYNTAX	INTEGER
			MAX-ACCESS	read-only
			STATUS	current
			::= { hmWanMbus18 94 }

hmWanMbus18Value2C		OBJECT-TYPE
			SYNTAX	INTEGER
			MAX-ACCESS	read-only
			STATUS	current
			::= { hmWanMbus18 95 }

hmWanMbus18VIF2D		OBJECT-TYPE
			SYNTAX	INTEGER
			MAX-ACCESS	read-only
			STATUS	current
			::= { hmWanMbus18 96 }

hmWanMbus18Value2D		OBJECT-TYPE
			SYNTAX	INTEGER
			MAX-ACCESS	read-only
			STATUS	current
			::= { hmWanMbus18 97 }

hmWanMbus18VIF2E		OBJECT-TYPE
			SYNTAX	INTEGER
			MAX-ACCESS	read-only
			STATUS	current
			::= { hmWanMbus18 98 }

hmWanMbus18Value2E		OBJECT-TYPE
			SYNTAX	INTEGER
			MAX-ACCESS	read-only
			STATUS	current
			::= { hmWanMbus18 99 }

hmWanMbus18VIF2F		OBJECT-TYPE
			SYNTAX	INTEGER
			MAX-ACCESS	read-only
			STATUS	current
			::= { hmWanMbus18 100 }

hmWanMbus18Value2F		OBJECT-TYPE
			SYNTAX	INTEGER
			MAX-ACCESS	read-only
			STATUS	current
			::= { hmWanMbus18 101 }

hmWanMbus19			OBJECT IDENTIFIER ::= { hmWanMbus 25 }

hmWanMbus19IdNumber		OBJECT-TYPE
			SYNTAX	Gauge32
			MAX-ACCESS	read-only
			STATUS	current
			::= { hmWanMbus19 1 }

hmWanMbus19Manufacturer	OBJECT-TYPE
			SYNTAX	Gauge32
			MAX-ACCESS	read-only
			STATUS	current
			::= { hmWanMbus19 2 }

hmWanMbus19Version		OBJECT-TYPE
			SYNTAX	Gauge32
			MAX-ACCESS	read-only
			STATUS	current
			::= { hmWanMbus19 3 }

hmWanMbus19Medium		OBJECT-TYPE
			SYNTAX	Gauge32
			MAX-ACCESS	read-only
			STATUS	current
			::= { hmWanMbus19 4 }

hmWanMbus19Status		OBJECT-TYPE
			SYNTAX	Gauge32
			MAX-ACCESS	read-only
			STATUS	current
			::= { hmWanMbus19 5 }

hmWanMbus19VIF00		OBJECT-TYPE
			SYNTAX	INTEGER
			MAX-ACCESS	read-only
			STATUS	current
			::= { hmWanMbus19 6 }

hmWanMbus19Value00		OBJECT-TYPE
			SYNTAX	INTEGER
			MAX-ACCESS	read-only
			STATUS	current
			::= { hmWanMbus19 7 }

hmWanMbus19VIF01		OBJECT-TYPE
			SYNTAX	INTEGER
			MAX-ACCESS	read-only
			STATUS	current
			::= { hmWanMbus19 8 }

hmWanMbus19Value01		OBJECT-TYPE
			SYNTAX	INTEGER
			MAX-ACCESS	read-only
			STATUS	current
			::= { hmWanMbus19 9 }

hmWanMbus19VIF02		OBJECT-TYPE
			SYNTAX	INTEGER
			MAX-ACCESS	read-only
			STATUS	current
			::= { hmWanMbus19 10 }

hmWanMbus19Value02		OBJECT-TYPE
			SYNTAX	INTEGER
			MAX-ACCESS	read-only
			STATUS	current
			::= { hmWanMbus19 11 }

hmWanMbus19VIF03		OBJECT-TYPE
			SYNTAX	INTEGER
			MAX-ACCESS	read-only
			STATUS	current
			::= { hmWanMbus19 12 }

hmWanMbus19Value03		OBJECT-TYPE
			SYNTAX	INTEGER
			MAX-ACCESS	read-only
			STATUS	current
			::= { hmWanMbus19 13 }

hmWanMbus19VIF04		OBJECT-TYPE
			SYNTAX	INTEGER
			MAX-ACCESS	read-only
			STATUS	current
			::= { hmWanMbus19 14 }

hmWanMbus19Value04		OBJECT-TYPE
			SYNTAX	INTEGER
			MAX-ACCESS	read-only
			STATUS	current
			::= { hmWanMbus19 15 }

hmWanMbus19VIF05		OBJECT-TYPE
			SYNTAX	INTEGER
			MAX-ACCESS	read-only
			STATUS	current
			::= { hmWanMbus19 16 }

hmWanMbus19Value05		OBJECT-TYPE
			SYNTAX	INTEGER
			MAX-ACCESS	read-only
			STATUS	current
			::= { hmWanMbus19 17 }

hmWanMbus19VIF06		OBJECT-TYPE
			SYNTAX	INTEGER
			MAX-ACCESS	read-only
			STATUS	current
			::= { hmWanMbus19 18 }

hmWanMbus19Value06		OBJECT-TYPE
			SYNTAX	INTEGER
			MAX-ACCESS	read-only
			STATUS	current
			::= { hmWanMbus19 19 }

hmWanMbus19VIF07		OBJECT-TYPE
			SYNTAX	INTEGER
			MAX-ACCESS	read-only
			STATUS	current
			::= { hmWanMbus19 20 }

hmWanMbus19Value07		OBJECT-TYPE
			SYNTAX	INTEGER
			MAX-ACCESS	read-only
			STATUS	current
			::= { hmWanMbus19 21 }

hmWanMbus19VIF08		OBJECT-TYPE
			SYNTAX	INTEGER
			MAX-ACCESS	read-only
			STATUS	current
			::= { hmWanMbus19 22 }

hmWanMbus19Value08		OBJECT-TYPE
			SYNTAX	INTEGER
			MAX-ACCESS	read-only
			STATUS	current
			::= { hmWanMbus19 23 }

hmWanMbus19VIF09		OBJECT-TYPE
			SYNTAX	INTEGER
			MAX-ACCESS	read-only
			STATUS	current
			::= { hmWanMbus19 24 }

hmWanMbus19Value09		OBJECT-TYPE
			SYNTAX	INTEGER
			MAX-ACCESS	read-only
			STATUS	current
			::= { hmWanMbus19 25 }

hmWanMbus19VIF0A		OBJECT-TYPE
			SYNTAX	INTEGER
			MAX-ACCESS	read-only
			STATUS	current
			::= { hmWanMbus19 26 }

hmWanMbus19Value0A		OBJECT-TYPE
			SYNTAX	INTEGER
			MAX-ACCESS	read-only
			STATUS	current
			::= { hmWanMbus19 27 }

hmWanMbus19VIF0B		OBJECT-TYPE
			SYNTAX	INTEGER
			MAX-ACCESS	read-only
			STATUS	current
			::= { hmWanMbus19 28 }

hmWanMbus19Value0B		OBJECT-TYPE
			SYNTAX	INTEGER
			MAX-ACCESS	read-only
			STATUS	current
			::= { hmWanMbus19 29 }

hmWanMbus19VIF0C		OBJECT-TYPE
			SYNTAX	INTEGER
			MAX-ACCESS	read-only
			STATUS	current
			::= { hmWanMbus19 30 }

hmWanMbus19Value0C		OBJECT-TYPE
			SYNTAX	INTEGER
			MAX-ACCESS	read-only
			STATUS	current
			::= { hmWanMbus19 31 }

hmWanMbus19VIF0D		OBJECT-TYPE
			SYNTAX	INTEGER
			MAX-ACCESS	read-only
			STATUS	current
			::= { hmWanMbus19 32 }

hmWanMbus19Value0D		OBJECT-TYPE
			SYNTAX	INTEGER
			MAX-ACCESS	read-only
			STATUS	current
			::= { hmWanMbus19 33 }

hmWanMbus19VIF0E		OBJECT-TYPE
			SYNTAX	INTEGER
			MAX-ACCESS	read-only
			STATUS	current
			::= { hmWanMbus19 34 }

hmWanMbus19Value0E		OBJECT-TYPE
			SYNTAX	INTEGER
			MAX-ACCESS	read-only
			STATUS	current
			::= { hmWanMbus19 35 }

hmWanMbus19VIF0F		OBJECT-TYPE
			SYNTAX	INTEGER
			MAX-ACCESS	read-only
			STATUS	current
			::= { hmWanMbus19 36 }

hmWanMbus19Value0F		OBJECT-TYPE
			SYNTAX	INTEGER
			MAX-ACCESS	read-only
			STATUS	current
			::= { hmWanMbus19 37 }

hmWanMbus19VIF10		OBJECT-TYPE
			SYNTAX	INTEGER
			MAX-ACCESS	read-only
			STATUS	current
			::= { hmWanMbus19 38 }

hmWanMbus19Value10		OBJECT-TYPE
			SYNTAX	INTEGER
			MAX-ACCESS	read-only
			STATUS	current
			::= { hmWanMbus19 39 }

hmWanMbus19VIF11		OBJECT-TYPE
			SYNTAX	INTEGER
			MAX-ACCESS	read-only
			STATUS	current
			::= { hmWanMbus19 40 }

hmWanMbus19Value11		OBJECT-TYPE
			SYNTAX	INTEGER
			MAX-ACCESS	read-only
			STATUS	current
			::= { hmWanMbus19 41 }

hmWanMbus19VIF12		OBJECT-TYPE
			SYNTAX	INTEGER
			MAX-ACCESS	read-only
			STATUS	current
			::= { hmWanMbus19 42 }

hmWanMbus19Value12		OBJECT-TYPE
			SYNTAX	INTEGER
			MAX-ACCESS	read-only
			STATUS	current
			::= { hmWanMbus19 43 }

hmWanMbus19VIF13		OBJECT-TYPE
			SYNTAX	INTEGER
			MAX-ACCESS	read-only
			STATUS	current
			::= { hmWanMbus19 44 }

hmWanMbus19Value13		OBJECT-TYPE
			SYNTAX	INTEGER
			MAX-ACCESS	read-only
			STATUS	current
			::= { hmWanMbus19 45 }

hmWanMbus19VIF14		OBJECT-TYPE
			SYNTAX	INTEGER
			MAX-ACCESS	read-only
			STATUS	current
			::= { hmWanMbus19 46 }

hmWanMbus19Value14		OBJECT-TYPE
			SYNTAX	INTEGER
			MAX-ACCESS	read-only
			STATUS	current
			::= { hmWanMbus19 47 }

hmWanMbus19VIF15		OBJECT-TYPE
			SYNTAX	INTEGER
			MAX-ACCESS	read-only
			STATUS	current
			::= { hmWanMbus19 48 }

hmWanMbus19Value15		OBJECT-TYPE
			SYNTAX	INTEGER
			MAX-ACCESS	read-only
			STATUS	current
			::= { hmWanMbus19 49 }

hmWanMbus19VIF16		OBJECT-TYPE
			SYNTAX	INTEGER
			MAX-ACCESS	read-only
			STATUS	current
			::= { hmWanMbus19 50 }

hmWanMbus19Value16		OBJECT-TYPE
			SYNTAX	INTEGER
			MAX-ACCESS	read-only
			STATUS	current
			::= { hmWanMbus19 51 }

hmWanMbus19VIF17		OBJECT-TYPE
			SYNTAX	INTEGER
			MAX-ACCESS	read-only
			STATUS	current
			::= { hmWanMbus19 52 }

hmWanMbus19Value17		OBJECT-TYPE
			SYNTAX	INTEGER
			MAX-ACCESS	read-only
			STATUS	current
			::= { hmWanMbus19 53 }

hmWanMbus19VIF18		OBJECT-TYPE
			SYNTAX	INTEGER
			MAX-ACCESS	read-only
			STATUS	current
			::= { hmWanMbus19 54 }

hmWanMbus19Value18		OBJECT-TYPE
			SYNTAX	INTEGER
			MAX-ACCESS	read-only
			STATUS	current
			::= { hmWanMbus19 55 }

hmWanMbus19VIF19		OBJECT-TYPE
			SYNTAX	INTEGER
			MAX-ACCESS	read-only
			STATUS	current
			::= { hmWanMbus19 56 }

hmWanMbus19Value19		OBJECT-TYPE
			SYNTAX	INTEGER
			MAX-ACCESS	read-only
			STATUS	current
			::= { hmWanMbus19 57 }

hmWanMbus19VIF1A		OBJECT-TYPE
			SYNTAX	INTEGER
			MAX-ACCESS	read-only
			STATUS	current
			::= { hmWanMbus19 58 }

hmWanMbus19Value1A		OBJECT-TYPE
			SYNTAX	INTEGER
			MAX-ACCESS	read-only
			STATUS	current
			::= { hmWanMbus19 59 }

hmWanMbus19VIF1B		OBJECT-TYPE
			SYNTAX	INTEGER
			MAX-ACCESS	read-only
			STATUS	current
			::= { hmWanMbus19 60 }

hmWanMbus19Value1B		OBJECT-TYPE
			SYNTAX	INTEGER
			MAX-ACCESS	read-only
			STATUS	current
			::= { hmWanMbus19 61 }

hmWanMbus19VIF1C		OBJECT-TYPE
			SYNTAX	INTEGER
			MAX-ACCESS	read-only
			STATUS	current
			::= { hmWanMbus19 62 }

hmWanMbus19Value1C		OBJECT-TYPE
			SYNTAX	INTEGER
			MAX-ACCESS	read-only
			STATUS	current
			::= { hmWanMbus19 63 }

hmWanMbus19VIF1D		OBJECT-TYPE
			SYNTAX	INTEGER
			MAX-ACCESS	read-only
			STATUS	current
			::= { hmWanMbus19 64 }

hmWanMbus19Value1D		OBJECT-TYPE
			SYNTAX	INTEGER
			MAX-ACCESS	read-only
			STATUS	current
			::= { hmWanMbus19 65 }

hmWanMbus19VIF1E		OBJECT-TYPE
			SYNTAX	INTEGER
			MAX-ACCESS	read-only
			STATUS	current
			::= { hmWanMbus19 66 }

hmWanMbus19Value1E		OBJECT-TYPE
			SYNTAX	INTEGER
			MAX-ACCESS	read-only
			STATUS	current
			::= { hmWanMbus19 67 }

hmWanMbus19VIF1F		OBJECT-TYPE
			SYNTAX	INTEGER
			MAX-ACCESS	read-only
			STATUS	current
			::= { hmWanMbus19 68 }

hmWanMbus19Value1F		OBJECT-TYPE
			SYNTAX	INTEGER
			MAX-ACCESS	read-only
			STATUS	current
			::= { hmWanMbus19 69 }

hmWanMbus19VIF20		OBJECT-TYPE
			SYNTAX	INTEGER
			MAX-ACCESS	read-only
			STATUS	current
			::= { hmWanMbus19 70 }

hmWanMbus19Value20		OBJECT-TYPE
			SYNTAX	INTEGER
			MAX-ACCESS	read-only
			STATUS	current
			::= { hmWanMbus19 71 }

hmWanMbus19VIF21		OBJECT-TYPE
			SYNTAX	INTEGER
			MAX-ACCESS	read-only
			STATUS	current
			::= { hmWanMbus19 72 }

hmWanMbus19Value21		OBJECT-TYPE
			SYNTAX	INTEGER
			MAX-ACCESS	read-only
			STATUS	current
			::= { hmWanMbus19 73 }

hmWanMbus19VIF22		OBJECT-TYPE
			SYNTAX	INTEGER
			MAX-ACCESS	read-only
			STATUS	current
			::= { hmWanMbus19 74 }

hmWanMbus19Value22		OBJECT-TYPE
			SYNTAX	INTEGER
			MAX-ACCESS	read-only
			STATUS	current
			::= { hmWanMbus19 75 }

hmWanMbus19VIF23		OBJECT-TYPE
			SYNTAX	INTEGER
			MAX-ACCESS	read-only
			STATUS	current
			::= { hmWanMbus19 76 }

hmWanMbus19Value23		OBJECT-TYPE
			SYNTAX	INTEGER
			MAX-ACCESS	read-only
			STATUS	current
			::= { hmWanMbus19 77 }

hmWanMbus19VIF24		OBJECT-TYPE
			SYNTAX	INTEGER
			MAX-ACCESS	read-only
			STATUS	current
			::= { hmWanMbus19 78 }

hmWanMbus19Value24		OBJECT-TYPE
			SYNTAX	INTEGER
			MAX-ACCESS	read-only
			STATUS	current
			::= { hmWanMbus19 79 }

hmWanMbus19VIF25		OBJECT-TYPE
			SYNTAX	INTEGER
			MAX-ACCESS	read-only
			STATUS	current
			::= { hmWanMbus19 80 }

hmWanMbus19Value25		OBJECT-TYPE
			SYNTAX	INTEGER
			MAX-ACCESS	read-only
			STATUS	current
			::= { hmWanMbus19 81 }

hmWanMbus19VIF26		OBJECT-TYPE
			SYNTAX	INTEGER
			MAX-ACCESS	read-only
			STATUS	current
			::= { hmWanMbus19 82 }

hmWanMbus19Value26		OBJECT-TYPE
			SYNTAX	INTEGER
			MAX-ACCESS	read-only
			STATUS	current
			::= { hmWanMbus19 83 }

hmWanMbus19VIF27		OBJECT-TYPE
			SYNTAX	INTEGER
			MAX-ACCESS	read-only
			STATUS	current
			::= { hmWanMbus19 84 }

hmWanMbus19Value27		OBJECT-TYPE
			SYNTAX	INTEGER
			MAX-ACCESS	read-only
			STATUS	current
			::= { hmWanMbus19 85 }

hmWanMbus19VIF28		OBJECT-TYPE
			SYNTAX	INTEGER
			MAX-ACCESS	read-only
			STATUS	current
			::= { hmWanMbus19 86 }

hmWanMbus19Value28		OBJECT-TYPE
			SYNTAX	INTEGER
			MAX-ACCESS	read-only
			STATUS	current
			::= { hmWanMbus19 87 }

hmWanMbus19VIF29		OBJECT-TYPE
			SYNTAX	INTEGER
			MAX-ACCESS	read-only
			STATUS	current
			::= { hmWanMbus19 88 }

hmWanMbus19Value29		OBJECT-TYPE
			SYNTAX	INTEGER
			MAX-ACCESS	read-only
			STATUS	current
			::= { hmWanMbus19 89 }

hmWanMbus19VIF2A		OBJECT-TYPE
			SYNTAX	INTEGER
			MAX-ACCESS	read-only
			STATUS	current
			::= { hmWanMbus19 90 }

hmWanMbus19Value2A		OBJECT-TYPE
			SYNTAX	INTEGER
			MAX-ACCESS	read-only
			STATUS	current
			::= { hmWanMbus19 91 }

hmWanMbus19VIF2B		OBJECT-TYPE
			SYNTAX	INTEGER
			MAX-ACCESS	read-only
			STATUS	current
			::= { hmWanMbus19 92 }

hmWanMbus19Value2B		OBJECT-TYPE
			SYNTAX	INTEGER
			MAX-ACCESS	read-only
			STATUS	current
			::= { hmWanMbus19 93 }

hmWanMbus19VIF2C		OBJECT-TYPE
			SYNTAX	INTEGER
			MAX-ACCESS	read-only
			STATUS	current
			::= { hmWanMbus19 94 }

hmWanMbus19Value2C		OBJECT-TYPE
			SYNTAX	INTEGER
			MAX-ACCESS	read-only
			STATUS	current
			::= { hmWanMbus19 95 }

hmWanMbus19VIF2D		OBJECT-TYPE
			SYNTAX	INTEGER
			MAX-ACCESS	read-only
			STATUS	current
			::= { hmWanMbus19 96 }

hmWanMbus19Value2D		OBJECT-TYPE
			SYNTAX	INTEGER
			MAX-ACCESS	read-only
			STATUS	current
			::= { hmWanMbus19 97 }

hmWanMbus19VIF2E		OBJECT-TYPE
			SYNTAX	INTEGER
			MAX-ACCESS	read-only
			STATUS	current
			::= { hmWanMbus19 98 }

hmWanMbus19Value2E		OBJECT-TYPE
			SYNTAX	INTEGER
			MAX-ACCESS	read-only
			STATUS	current
			::= { hmWanMbus19 99 }

hmWanMbus19VIF2F		OBJECT-TYPE
			SYNTAX	INTEGER
			MAX-ACCESS	read-only
			STATUS	current
			::= { hmWanMbus19 100 }

hmWanMbus19Value2F		OBJECT-TYPE
			SYNTAX	INTEGER
			MAX-ACCESS	read-only
			STATUS	current
			::= { hmWanMbus19 101 }

hmWanMbus1A			OBJECT IDENTIFIER ::= { hmWanMbus 26 }

hmWanMbus1AIdNumber		OBJECT-TYPE
			SYNTAX	Gauge32
			MAX-ACCESS	read-only
			STATUS	current
			::= { hmWanMbus1A 1 }

hmWanMbus1AManufacturer	OBJECT-TYPE
			SYNTAX	Gauge32
			MAX-ACCESS	read-only
			STATUS	current
			::= { hmWanMbus1A 2 }

hmWanMbus1AVersion		OBJECT-TYPE
			SYNTAX	Gauge32
			MAX-ACCESS	read-only
			STATUS	current
			::= { hmWanMbus1A 3 }

hmWanMbus1AMedium		OBJECT-TYPE
			SYNTAX	Gauge32
			MAX-ACCESS	read-only
			STATUS	current
			::= { hmWanMbus1A 4 }

hmWanMbus1AStatus		OBJECT-TYPE
			SYNTAX	Gauge32
			MAX-ACCESS	read-only
			STATUS	current
			::= { hmWanMbus1A 5 }

hmWanMbus1AVIF00		OBJECT-TYPE
			SYNTAX	INTEGER
			MAX-ACCESS	read-only
			STATUS	current
			::= { hmWanMbus1A 6 }

hmWanMbus1AValue00		OBJECT-TYPE
			SYNTAX	INTEGER
			MAX-ACCESS	read-only
			STATUS	current
			::= { hmWanMbus1A 7 }

hmWanMbus1AVIF01		OBJECT-TYPE
			SYNTAX	INTEGER
			MAX-ACCESS	read-only
			STATUS	current
			::= { hmWanMbus1A 8 }

hmWanMbus1AValue01		OBJECT-TYPE
			SYNTAX	INTEGER
			MAX-ACCESS	read-only
			STATUS	current
			::= { hmWanMbus1A 9 }

hmWanMbus1AVIF02		OBJECT-TYPE
			SYNTAX	INTEGER
			MAX-ACCESS	read-only
			STATUS	current
			::= { hmWanMbus1A 10 }

hmWanMbus1AValue02		OBJECT-TYPE
			SYNTAX	INTEGER
			MAX-ACCESS	read-only
			STATUS	current
			::= { hmWanMbus1A 11 }

hmWanMbus1AVIF03		OBJECT-TYPE
			SYNTAX	INTEGER
			MAX-ACCESS	read-only
			STATUS	current
			::= { hmWanMbus1A 12 }

hmWanMbus1AValue03		OBJECT-TYPE
			SYNTAX	INTEGER
			MAX-ACCESS	read-only
			STATUS	current
			::= { hmWanMbus1A 13 }

hmWanMbus1AVIF04		OBJECT-TYPE
			SYNTAX	INTEGER
			MAX-ACCESS	read-only
			STATUS	current
			::= { hmWanMbus1A 14 }

hmWanMbus1AValue04		OBJECT-TYPE
			SYNTAX	INTEGER
			MAX-ACCESS	read-only
			STATUS	current
			::= { hmWanMbus1A 15 }

hmWanMbus1AVIF05		OBJECT-TYPE
			SYNTAX	INTEGER
			MAX-ACCESS	read-only
			STATUS	current
			::= { hmWanMbus1A 16 }

hmWanMbus1AValue05		OBJECT-TYPE
			SYNTAX	INTEGER
			MAX-ACCESS	read-only
			STATUS	current
			::= { hmWanMbus1A 17 }

hmWanMbus1AVIF06		OBJECT-TYPE
			SYNTAX	INTEGER
			MAX-ACCESS	read-only
			STATUS	current
			::= { hmWanMbus1A 18 }

hmWanMbus1AValue06		OBJECT-TYPE
			SYNTAX	INTEGER
			MAX-ACCESS	read-only
			STATUS	current
			::= { hmWanMbus1A 19 }

hmWanMbus1AVIF07		OBJECT-TYPE
			SYNTAX	INTEGER
			MAX-ACCESS	read-only
			STATUS	current
			::= { hmWanMbus1A 20 }

hmWanMbus1AValue07		OBJECT-TYPE
			SYNTAX	INTEGER
			MAX-ACCESS	read-only
			STATUS	current
			::= { hmWanMbus1A 21 }

hmWanMbus1AVIF08		OBJECT-TYPE
			SYNTAX	INTEGER
			MAX-ACCESS	read-only
			STATUS	current
			::= { hmWanMbus1A 22 }

hmWanMbus1AValue08		OBJECT-TYPE
			SYNTAX	INTEGER
			MAX-ACCESS	read-only
			STATUS	current
			::= { hmWanMbus1A 23 }

hmWanMbus1AVIF09		OBJECT-TYPE
			SYNTAX	INTEGER
			MAX-ACCESS	read-only
			STATUS	current
			::= { hmWanMbus1A 24 }

hmWanMbus1AValue09		OBJECT-TYPE
			SYNTAX	INTEGER
			MAX-ACCESS	read-only
			STATUS	current
			::= { hmWanMbus1A 25 }

hmWanMbus1AVIF0A		OBJECT-TYPE
			SYNTAX	INTEGER
			MAX-ACCESS	read-only
			STATUS	current
			::= { hmWanMbus1A 26 }

hmWanMbus1AValue0A		OBJECT-TYPE
			SYNTAX	INTEGER
			MAX-ACCESS	read-only
			STATUS	current
			::= { hmWanMbus1A 27 }

hmWanMbus1AVIF0B		OBJECT-TYPE
			SYNTAX	INTEGER
			MAX-ACCESS	read-only
			STATUS	current
			::= { hmWanMbus1A 28 }

hmWanMbus1AValue0B		OBJECT-TYPE
			SYNTAX	INTEGER
			MAX-ACCESS	read-only
			STATUS	current
			::= { hmWanMbus1A 29 }

hmWanMbus1AVIF0C		OBJECT-TYPE
			SYNTAX	INTEGER
			MAX-ACCESS	read-only
			STATUS	current
			::= { hmWanMbus1A 30 }

hmWanMbus1AValue0C		OBJECT-TYPE
			SYNTAX	INTEGER
			MAX-ACCESS	read-only
			STATUS	current
			::= { hmWanMbus1A 31 }

hmWanMbus1AVIF0D		OBJECT-TYPE
			SYNTAX	INTEGER
			MAX-ACCESS	read-only
			STATUS	current
			::= { hmWanMbus1A 32 }

hmWanMbus1AValue0D		OBJECT-TYPE
			SYNTAX	INTEGER
			MAX-ACCESS	read-only
			STATUS	current
			::= { hmWanMbus1A 33 }

hmWanMbus1AVIF0E		OBJECT-TYPE
			SYNTAX	INTEGER
			MAX-ACCESS	read-only
			STATUS	current
			::= { hmWanMbus1A 34 }

hmWanMbus1AValue0E		OBJECT-TYPE
			SYNTAX	INTEGER
			MAX-ACCESS	read-only
			STATUS	current
			::= { hmWanMbus1A 35 }

hmWanMbus1AVIF0F		OBJECT-TYPE
			SYNTAX	INTEGER
			MAX-ACCESS	read-only
			STATUS	current
			::= { hmWanMbus1A 36 }

hmWanMbus1AValue0F		OBJECT-TYPE
			SYNTAX	INTEGER
			MAX-ACCESS	read-only
			STATUS	current
			::= { hmWanMbus1A 37 }

hmWanMbus1AVIF10		OBJECT-TYPE
			SYNTAX	INTEGER
			MAX-ACCESS	read-only
			STATUS	current
			::= { hmWanMbus1A 38 }

hmWanMbus1AValue10		OBJECT-TYPE
			SYNTAX	INTEGER
			MAX-ACCESS	read-only
			STATUS	current
			::= { hmWanMbus1A 39 }

hmWanMbus1AVIF11		OBJECT-TYPE
			SYNTAX	INTEGER
			MAX-ACCESS	read-only
			STATUS	current
			::= { hmWanMbus1A 40 }

hmWanMbus1AValue11		OBJECT-TYPE
			SYNTAX	INTEGER
			MAX-ACCESS	read-only
			STATUS	current
			::= { hmWanMbus1A 41 }

hmWanMbus1AVIF12		OBJECT-TYPE
			SYNTAX	INTEGER
			MAX-ACCESS	read-only
			STATUS	current
			::= { hmWanMbus1A 42 }

hmWanMbus1AValue12		OBJECT-TYPE
			SYNTAX	INTEGER
			MAX-ACCESS	read-only
			STATUS	current
			::= { hmWanMbus1A 43 }

hmWanMbus1AVIF13		OBJECT-TYPE
			SYNTAX	INTEGER
			MAX-ACCESS	read-only
			STATUS	current
			::= { hmWanMbus1A 44 }

hmWanMbus1AValue13		OBJECT-TYPE
			SYNTAX	INTEGER
			MAX-ACCESS	read-only
			STATUS	current
			::= { hmWanMbus1A 45 }

hmWanMbus1AVIF14		OBJECT-TYPE
			SYNTAX	INTEGER
			MAX-ACCESS	read-only
			STATUS	current
			::= { hmWanMbus1A 46 }

hmWanMbus1AValue14		OBJECT-TYPE
			SYNTAX	INTEGER
			MAX-ACCESS	read-only
			STATUS	current
			::= { hmWanMbus1A 47 }

hmWanMbus1AVIF15		OBJECT-TYPE
			SYNTAX	INTEGER
			MAX-ACCESS	read-only
			STATUS	current
			::= { hmWanMbus1A 48 }

hmWanMbus1AValue15		OBJECT-TYPE
			SYNTAX	INTEGER
			MAX-ACCESS	read-only
			STATUS	current
			::= { hmWanMbus1A 49 }

hmWanMbus1AVIF16		OBJECT-TYPE
			SYNTAX	INTEGER
			MAX-ACCESS	read-only
			STATUS	current
			::= { hmWanMbus1A 50 }

hmWanMbus1AValue16		OBJECT-TYPE
			SYNTAX	INTEGER
			MAX-ACCESS	read-only
			STATUS	current
			::= { hmWanMbus1A 51 }

hmWanMbus1AVIF17		OBJECT-TYPE
			SYNTAX	INTEGER
			MAX-ACCESS	read-only
			STATUS	current
			::= { hmWanMbus1A 52 }

hmWanMbus1AValue17		OBJECT-TYPE
			SYNTAX	INTEGER
			MAX-ACCESS	read-only
			STATUS	current
			::= { hmWanMbus1A 53 }

hmWanMbus1AVIF18		OBJECT-TYPE
			SYNTAX	INTEGER
			MAX-ACCESS	read-only
			STATUS	current
			::= { hmWanMbus1A 54 }

hmWanMbus1AValue18		OBJECT-TYPE
			SYNTAX	INTEGER
			MAX-ACCESS	read-only
			STATUS	current
			::= { hmWanMbus1A 55 }

hmWanMbus1AVIF19		OBJECT-TYPE
			SYNTAX	INTEGER
			MAX-ACCESS	read-only
			STATUS	current
			::= { hmWanMbus1A 56 }

hmWanMbus1AValue19		OBJECT-TYPE
			SYNTAX	INTEGER
			MAX-ACCESS	read-only
			STATUS	current
			::= { hmWanMbus1A 57 }

hmWanMbus1AVIF1A		OBJECT-TYPE
			SYNTAX	INTEGER
			MAX-ACCESS	read-only
			STATUS	current
			::= { hmWanMbus1A 58 }

hmWanMbus1AValue1A		OBJECT-TYPE
			SYNTAX	INTEGER
			MAX-ACCESS	read-only
			STATUS	current
			::= { hmWanMbus1A 59 }

hmWanMbus1AVIF1B		OBJECT-TYPE
			SYNTAX	INTEGER
			MAX-ACCESS	read-only
			STATUS	current
			::= { hmWanMbus1A 60 }

hmWanMbus1AValue1B		OBJECT-TYPE
			SYNTAX	INTEGER
			MAX-ACCESS	read-only
			STATUS	current
			::= { hmWanMbus1A 61 }

hmWanMbus1AVIF1C		OBJECT-TYPE
			SYNTAX	INTEGER
			MAX-ACCESS	read-only
			STATUS	current
			::= { hmWanMbus1A 62 }

hmWanMbus1AValue1C		OBJECT-TYPE
			SYNTAX	INTEGER
			MAX-ACCESS	read-only
			STATUS	current
			::= { hmWanMbus1A 63 }

hmWanMbus1AVIF1D		OBJECT-TYPE
			SYNTAX	INTEGER
			MAX-ACCESS	read-only
			STATUS	current
			::= { hmWanMbus1A 64 }

hmWanMbus1AValue1D		OBJECT-TYPE
			SYNTAX	INTEGER
			MAX-ACCESS	read-only
			STATUS	current
			::= { hmWanMbus1A 65 }

hmWanMbus1AVIF1E		OBJECT-TYPE
			SYNTAX	INTEGER
			MAX-ACCESS	read-only
			STATUS	current
			::= { hmWanMbus1A 66 }

hmWanMbus1AValue1E		OBJECT-TYPE
			SYNTAX	INTEGER
			MAX-ACCESS	read-only
			STATUS	current
			::= { hmWanMbus1A 67 }

hmWanMbus1AVIF1F		OBJECT-TYPE
			SYNTAX	INTEGER
			MAX-ACCESS	read-only
			STATUS	current
			::= { hmWanMbus1A 68 }

hmWanMbus1AValue1F		OBJECT-TYPE
			SYNTAX	INTEGER
			MAX-ACCESS	read-only
			STATUS	current
			::= { hmWanMbus1A 69 }

hmWanMbus1AVIF20		OBJECT-TYPE
			SYNTAX	INTEGER
			MAX-ACCESS	read-only
			STATUS	current
			::= { hmWanMbus1A 70 }

hmWanMbus1AValue20		OBJECT-TYPE
			SYNTAX	INTEGER
			MAX-ACCESS	read-only
			STATUS	current
			::= { hmWanMbus1A 71 }

hmWanMbus1AVIF21		OBJECT-TYPE
			SYNTAX	INTEGER
			MAX-ACCESS	read-only
			STATUS	current
			::= { hmWanMbus1A 72 }

hmWanMbus1AValue21		OBJECT-TYPE
			SYNTAX	INTEGER
			MAX-ACCESS	read-only
			STATUS	current
			::= { hmWanMbus1A 73 }

hmWanMbus1AVIF22		OBJECT-TYPE
			SYNTAX	INTEGER
			MAX-ACCESS	read-only
			STATUS	current
			::= { hmWanMbus1A 74 }

hmWanMbus1AValue22		OBJECT-TYPE
			SYNTAX	INTEGER
			MAX-ACCESS	read-only
			STATUS	current
			::= { hmWanMbus1A 75 }

hmWanMbus1AVIF23		OBJECT-TYPE
			SYNTAX	INTEGER
			MAX-ACCESS	read-only
			STATUS	current
			::= { hmWanMbus1A 76 }

hmWanMbus1AValue23		OBJECT-TYPE
			SYNTAX	INTEGER
			MAX-ACCESS	read-only
			STATUS	current
			::= { hmWanMbus1A 77 }

hmWanMbus1AVIF24		OBJECT-TYPE
			SYNTAX	INTEGER
			MAX-ACCESS	read-only
			STATUS	current
			::= { hmWanMbus1A 78 }

hmWanMbus1AValue24		OBJECT-TYPE
			SYNTAX	INTEGER
			MAX-ACCESS	read-only
			STATUS	current
			::= { hmWanMbus1A 79 }

hmWanMbus1AVIF25		OBJECT-TYPE
			SYNTAX	INTEGER
			MAX-ACCESS	read-only
			STATUS	current
			::= { hmWanMbus1A 80 }

hmWanMbus1AValue25		OBJECT-TYPE
			SYNTAX	INTEGER
			MAX-ACCESS	read-only
			STATUS	current
			::= { hmWanMbus1A 81 }

hmWanMbus1AVIF26		OBJECT-TYPE
			SYNTAX	INTEGER
			MAX-ACCESS	read-only
			STATUS	current
			::= { hmWanMbus1A 82 }

hmWanMbus1AValue26		OBJECT-TYPE
			SYNTAX	INTEGER
			MAX-ACCESS	read-only
			STATUS	current
			::= { hmWanMbus1A 83 }

hmWanMbus1AVIF27		OBJECT-TYPE
			SYNTAX	INTEGER
			MAX-ACCESS	read-only
			STATUS	current
			::= { hmWanMbus1A 84 }

hmWanMbus1AValue27		OBJECT-TYPE
			SYNTAX	INTEGER
			MAX-ACCESS	read-only
			STATUS	current
			::= { hmWanMbus1A 85 }

hmWanMbus1AVIF28		OBJECT-TYPE
			SYNTAX	INTEGER
			MAX-ACCESS	read-only
			STATUS	current
			::= { hmWanMbus1A 86 }

hmWanMbus1AValue28		OBJECT-TYPE
			SYNTAX	INTEGER
			MAX-ACCESS	read-only
			STATUS	current
			::= { hmWanMbus1A 87 }

hmWanMbus1AVIF29		OBJECT-TYPE
			SYNTAX	INTEGER
			MAX-ACCESS	read-only
			STATUS	current
			::= { hmWanMbus1A 88 }

hmWanMbus1AValue29		OBJECT-TYPE
			SYNTAX	INTEGER
			MAX-ACCESS	read-only
			STATUS	current
			::= { hmWanMbus1A 89 }

hmWanMbus1AVIF2A		OBJECT-TYPE
			SYNTAX	INTEGER
			MAX-ACCESS	read-only
			STATUS	current
			::= { hmWanMbus1A 90 }

hmWanMbus1AValue2A		OBJECT-TYPE
			SYNTAX	INTEGER
			MAX-ACCESS	read-only
			STATUS	current
			::= { hmWanMbus1A 91 }

hmWanMbus1AVIF2B		OBJECT-TYPE
			SYNTAX	INTEGER
			MAX-ACCESS	read-only
			STATUS	current
			::= { hmWanMbus1A 92 }

hmWanMbus1AValue2B		OBJECT-TYPE
			SYNTAX	INTEGER
			MAX-ACCESS	read-only
			STATUS	current
			::= { hmWanMbus1A 93 }

hmWanMbus1AVIF2C		OBJECT-TYPE
			SYNTAX	INTEGER
			MAX-ACCESS	read-only
			STATUS	current
			::= { hmWanMbus1A 94 }

hmWanMbus1AValue2C		OBJECT-TYPE
			SYNTAX	INTEGER
			MAX-ACCESS	read-only
			STATUS	current
			::= { hmWanMbus1A 95 }

hmWanMbus1AVIF2D		OBJECT-TYPE
			SYNTAX	INTEGER
			MAX-ACCESS	read-only
			STATUS	current
			::= { hmWanMbus1A 96 }

hmWanMbus1AValue2D		OBJECT-TYPE
			SYNTAX	INTEGER
			MAX-ACCESS	read-only
			STATUS	current
			::= { hmWanMbus1A 97 }

hmWanMbus1AVIF2E		OBJECT-TYPE
			SYNTAX	INTEGER
			MAX-ACCESS	read-only
			STATUS	current
			::= { hmWanMbus1A 98 }

hmWanMbus1AValue2E		OBJECT-TYPE
			SYNTAX	INTEGER
			MAX-ACCESS	read-only
			STATUS	current
			::= { hmWanMbus1A 99 }

hmWanMbus1AVIF2F		OBJECT-TYPE
			SYNTAX	INTEGER
			MAX-ACCESS	read-only
			STATUS	current
			::= { hmWanMbus1A 100 }

hmWanMbus1AValue2F		OBJECT-TYPE
			SYNTAX	INTEGER
			MAX-ACCESS	read-only
			STATUS	current
			::= { hmWanMbus1A 101 }

hmWanMbus1B			OBJECT IDENTIFIER ::= { hmWanMbus 27 }

hmWanMbus1BIdNumber		OBJECT-TYPE
			SYNTAX	Gauge32
			MAX-ACCESS	read-only
			STATUS	current
			::= { hmWanMbus1B 1 }

hmWanMbus1BManufacturer	OBJECT-TYPE
			SYNTAX	Gauge32
			MAX-ACCESS	read-only
			STATUS	current
			::= { hmWanMbus1B 2 }

hmWanMbus1BVersion		OBJECT-TYPE
			SYNTAX	Gauge32
			MAX-ACCESS	read-only
			STATUS	current
			::= { hmWanMbus1B 3 }

hmWanMbus1BMedium		OBJECT-TYPE
			SYNTAX	Gauge32
			MAX-ACCESS	read-only
			STATUS	current
			::= { hmWanMbus1B 4 }

hmWanMbus1BStatus		OBJECT-TYPE
			SYNTAX	Gauge32
			MAX-ACCESS	read-only
			STATUS	current
			::= { hmWanMbus1B 5 }

hmWanMbus1BVIF00		OBJECT-TYPE
			SYNTAX	INTEGER
			MAX-ACCESS	read-only
			STATUS	current
			::= { hmWanMbus1B 6 }

hmWanMbus1BValue00		OBJECT-TYPE
			SYNTAX	INTEGER
			MAX-ACCESS	read-only
			STATUS	current
			::= { hmWanMbus1B 7 }

hmWanMbus1BVIF01		OBJECT-TYPE
			SYNTAX	INTEGER
			MAX-ACCESS	read-only
			STATUS	current
			::= { hmWanMbus1B 8 }

hmWanMbus1BValue01		OBJECT-TYPE
			SYNTAX	INTEGER
			MAX-ACCESS	read-only
			STATUS	current
			::= { hmWanMbus1B 9 }

hmWanMbus1BVIF02		OBJECT-TYPE
			SYNTAX	INTEGER
			MAX-ACCESS	read-only
			STATUS	current
			::= { hmWanMbus1B 10 }

hmWanMbus1BValue02		OBJECT-TYPE
			SYNTAX	INTEGER
			MAX-ACCESS	read-only
			STATUS	current
			::= { hmWanMbus1B 11 }

hmWanMbus1BVIF03		OBJECT-TYPE
			SYNTAX	INTEGER
			MAX-ACCESS	read-only
			STATUS	current
			::= { hmWanMbus1B 12 }

hmWanMbus1BValue03		OBJECT-TYPE
			SYNTAX	INTEGER
			MAX-ACCESS	read-only
			STATUS	current
			::= { hmWanMbus1B 13 }

hmWanMbus1BVIF04		OBJECT-TYPE
			SYNTAX	INTEGER
			MAX-ACCESS	read-only
			STATUS	current
			::= { hmWanMbus1B 14 }

hmWanMbus1BValue04		OBJECT-TYPE
			SYNTAX	INTEGER
			MAX-ACCESS	read-only
			STATUS	current
			::= { hmWanMbus1B 15 }

hmWanMbus1BVIF05		OBJECT-TYPE
			SYNTAX	INTEGER
			MAX-ACCESS	read-only
			STATUS	current
			::= { hmWanMbus1B 16 }

hmWanMbus1BValue05		OBJECT-TYPE
			SYNTAX	INTEGER
			MAX-ACCESS	read-only
			STATUS	current
			::= { hmWanMbus1B 17 }

hmWanMbus1BVIF06		OBJECT-TYPE
			SYNTAX	INTEGER
			MAX-ACCESS	read-only
			STATUS	current
			::= { hmWanMbus1B 18 }

hmWanMbus1BValue06		OBJECT-TYPE
			SYNTAX	INTEGER
			MAX-ACCESS	read-only
			STATUS	current
			::= { hmWanMbus1B 19 }

hmWanMbus1BVIF07		OBJECT-TYPE
			SYNTAX	INTEGER
			MAX-ACCESS	read-only
			STATUS	current
			::= { hmWanMbus1B 20 }

hmWanMbus1BValue07		OBJECT-TYPE
			SYNTAX	INTEGER
			MAX-ACCESS	read-only
			STATUS	current
			::= { hmWanMbus1B 21 }

hmWanMbus1BVIF08		OBJECT-TYPE
			SYNTAX	INTEGER
			MAX-ACCESS	read-only
			STATUS	current
			::= { hmWanMbus1B 22 }

hmWanMbus1BValue08		OBJECT-TYPE
			SYNTAX	INTEGER
			MAX-ACCESS	read-only
			STATUS	current
			::= { hmWanMbus1B 23 }

hmWanMbus1BVIF09		OBJECT-TYPE
			SYNTAX	INTEGER
			MAX-ACCESS	read-only
			STATUS	current
			::= { hmWanMbus1B 24 }

hmWanMbus1BValue09		OBJECT-TYPE
			SYNTAX	INTEGER
			MAX-ACCESS	read-only
			STATUS	current
			::= { hmWanMbus1B 25 }

hmWanMbus1BVIF0A		OBJECT-TYPE
			SYNTAX	INTEGER
			MAX-ACCESS	read-only
			STATUS	current
			::= { hmWanMbus1B 26 }

hmWanMbus1BValue0A		OBJECT-TYPE
			SYNTAX	INTEGER
			MAX-ACCESS	read-only
			STATUS	current
			::= { hmWanMbus1B 27 }

hmWanMbus1BVIF0B		OBJECT-TYPE
			SYNTAX	INTEGER
			MAX-ACCESS	read-only
			STATUS	current
			::= { hmWanMbus1B 28 }

hmWanMbus1BValue0B		OBJECT-TYPE
			SYNTAX	INTEGER
			MAX-ACCESS	read-only
			STATUS	current
			::= { hmWanMbus1B 29 }

hmWanMbus1BVIF0C		OBJECT-TYPE
			SYNTAX	INTEGER
			MAX-ACCESS	read-only
			STATUS	current
			::= { hmWanMbus1B 30 }

hmWanMbus1BValue0C		OBJECT-TYPE
			SYNTAX	INTEGER
			MAX-ACCESS	read-only
			STATUS	current
			::= { hmWanMbus1B 31 }

hmWanMbus1BVIF0D		OBJECT-TYPE
			SYNTAX	INTEGER
			MAX-ACCESS	read-only
			STATUS	current
			::= { hmWanMbus1B 32 }

hmWanMbus1BValue0D		OBJECT-TYPE
			SYNTAX	INTEGER
			MAX-ACCESS	read-only
			STATUS	current
			::= { hmWanMbus1B 33 }

hmWanMbus1BVIF0E		OBJECT-TYPE
			SYNTAX	INTEGER
			MAX-ACCESS	read-only
			STATUS	current
			::= { hmWanMbus1B 34 }

hmWanMbus1BValue0E		OBJECT-TYPE
			SYNTAX	INTEGER
			MAX-ACCESS	read-only
			STATUS	current
			::= { hmWanMbus1B 35 }

hmWanMbus1BVIF0F		OBJECT-TYPE
			SYNTAX	INTEGER
			MAX-ACCESS	read-only
			STATUS	current
			::= { hmWanMbus1B 36 }

hmWanMbus1BValue0F		OBJECT-TYPE
			SYNTAX	INTEGER
			MAX-ACCESS	read-only
			STATUS	current
			::= { hmWanMbus1B 37 }

hmWanMbus1BVIF10		OBJECT-TYPE
			SYNTAX	INTEGER
			MAX-ACCESS	read-only
			STATUS	current
			::= { hmWanMbus1B 38 }

hmWanMbus1BValue10		OBJECT-TYPE
			SYNTAX	INTEGER
			MAX-ACCESS	read-only
			STATUS	current
			::= { hmWanMbus1B 39 }

hmWanMbus1BVIF11		OBJECT-TYPE
			SYNTAX	INTEGER
			MAX-ACCESS	read-only
			STATUS	current
			::= { hmWanMbus1B 40 }

hmWanMbus1BValue11		OBJECT-TYPE
			SYNTAX	INTEGER
			MAX-ACCESS	read-only
			STATUS	current
			::= { hmWanMbus1B 41 }

hmWanMbus1BVIF12		OBJECT-TYPE
			SYNTAX	INTEGER
			MAX-ACCESS	read-only
			STATUS	current
			::= { hmWanMbus1B 42 }

hmWanMbus1BValue12		OBJECT-TYPE
			SYNTAX	INTEGER
			MAX-ACCESS	read-only
			STATUS	current
			::= { hmWanMbus1B 43 }

hmWanMbus1BVIF13		OBJECT-TYPE
			SYNTAX	INTEGER
			MAX-ACCESS	read-only
			STATUS	current
			::= { hmWanMbus1B 44 }

hmWanMbus1BValue13		OBJECT-TYPE
			SYNTAX	INTEGER
			MAX-ACCESS	read-only
			STATUS	current
			::= { hmWanMbus1B 45 }

hmWanMbus1BVIF14		OBJECT-TYPE
			SYNTAX	INTEGER
			MAX-ACCESS	read-only
			STATUS	current
			::= { hmWanMbus1B 46 }

hmWanMbus1BValue14		OBJECT-TYPE
			SYNTAX	INTEGER
			MAX-ACCESS	read-only
			STATUS	current
			::= { hmWanMbus1B 47 }

hmWanMbus1BVIF15		OBJECT-TYPE
			SYNTAX	INTEGER
			MAX-ACCESS	read-only
			STATUS	current
			::= { hmWanMbus1B 48 }

hmWanMbus1BValue15		OBJECT-TYPE
			SYNTAX	INTEGER
			MAX-ACCESS	read-only
			STATUS	current
			::= { hmWanMbus1B 49 }

hmWanMbus1BVIF16		OBJECT-TYPE
			SYNTAX	INTEGER
			MAX-ACCESS	read-only
			STATUS	current
			::= { hmWanMbus1B 50 }

hmWanMbus1BValue16		OBJECT-TYPE
			SYNTAX	INTEGER
			MAX-ACCESS	read-only
			STATUS	current
			::= { hmWanMbus1B 51 }

hmWanMbus1BVIF17		OBJECT-TYPE
			SYNTAX	INTEGER
			MAX-ACCESS	read-only
			STATUS	current
			::= { hmWanMbus1B 52 }

hmWanMbus1BValue17		OBJECT-TYPE
			SYNTAX	INTEGER
			MAX-ACCESS	read-only
			STATUS	current
			::= { hmWanMbus1B 53 }

hmWanMbus1BVIF18		OBJECT-TYPE
			SYNTAX	INTEGER
			MAX-ACCESS	read-only
			STATUS	current
			::= { hmWanMbus1B 54 }

hmWanMbus1BValue18		OBJECT-TYPE
			SYNTAX	INTEGER
			MAX-ACCESS	read-only
			STATUS	current
			::= { hmWanMbus1B 55 }

hmWanMbus1BVIF19		OBJECT-TYPE
			SYNTAX	INTEGER
			MAX-ACCESS	read-only
			STATUS	current
			::= { hmWanMbus1B 56 }

hmWanMbus1BValue19		OBJECT-TYPE
			SYNTAX	INTEGER
			MAX-ACCESS	read-only
			STATUS	current
			::= { hmWanMbus1B 57 }

hmWanMbus1BVIF1A		OBJECT-TYPE
			SYNTAX	INTEGER
			MAX-ACCESS	read-only
			STATUS	current
			::= { hmWanMbus1B 58 }

hmWanMbus1BValue1A		OBJECT-TYPE
			SYNTAX	INTEGER
			MAX-ACCESS	read-only
			STATUS	current
			::= { hmWanMbus1B 59 }

hmWanMbus1BVIF1B		OBJECT-TYPE
			SYNTAX	INTEGER
			MAX-ACCESS	read-only
			STATUS	current
			::= { hmWanMbus1B 60 }

hmWanMbus1BValue1B		OBJECT-TYPE
			SYNTAX	INTEGER
			MAX-ACCESS	read-only
			STATUS	current
			::= { hmWanMbus1B 61 }

hmWanMbus1BVIF1C		OBJECT-TYPE
			SYNTAX	INTEGER
			MAX-ACCESS	read-only
			STATUS	current
			::= { hmWanMbus1B 62 }

hmWanMbus1BValue1C		OBJECT-TYPE
			SYNTAX	INTEGER
			MAX-ACCESS	read-only
			STATUS	current
			::= { hmWanMbus1B 63 }

hmWanMbus1BVIF1D		OBJECT-TYPE
			SYNTAX	INTEGER
			MAX-ACCESS	read-only
			STATUS	current
			::= { hmWanMbus1B 64 }

hmWanMbus1BValue1D		OBJECT-TYPE
			SYNTAX	INTEGER
			MAX-ACCESS	read-only
			STATUS	current
			::= { hmWanMbus1B 65 }

hmWanMbus1BVIF1E		OBJECT-TYPE
			SYNTAX	INTEGER
			MAX-ACCESS	read-only
			STATUS	current
			::= { hmWanMbus1B 66 }

hmWanMbus1BValue1E		OBJECT-TYPE
			SYNTAX	INTEGER
			MAX-ACCESS	read-only
			STATUS	current
			::= { hmWanMbus1B 67 }

hmWanMbus1BVIF1F		OBJECT-TYPE
			SYNTAX	INTEGER
			MAX-ACCESS	read-only
			STATUS	current
			::= { hmWanMbus1B 68 }

hmWanMbus1BValue1F		OBJECT-TYPE
			SYNTAX	INTEGER
			MAX-ACCESS	read-only
			STATUS	current
			::= { hmWanMbus1B 69 }

hmWanMbus1BVIF20		OBJECT-TYPE
			SYNTAX	INTEGER
			MAX-ACCESS	read-only
			STATUS	current
			::= { hmWanMbus1B 70 }

hmWanMbus1BValue20		OBJECT-TYPE
			SYNTAX	INTEGER
			MAX-ACCESS	read-only
			STATUS	current
			::= { hmWanMbus1B 71 }

hmWanMbus1BVIF21		OBJECT-TYPE
			SYNTAX	INTEGER
			MAX-ACCESS	read-only
			STATUS	current
			::= { hmWanMbus1B 72 }

hmWanMbus1BValue21		OBJECT-TYPE
			SYNTAX	INTEGER
			MAX-ACCESS	read-only
			STATUS	current
			::= { hmWanMbus1B 73 }

hmWanMbus1BVIF22		OBJECT-TYPE
			SYNTAX	INTEGER
			MAX-ACCESS	read-only
			STATUS	current
			::= { hmWanMbus1B 74 }

hmWanMbus1BValue22		OBJECT-TYPE
			SYNTAX	INTEGER
			MAX-ACCESS	read-only
			STATUS	current
			::= { hmWanMbus1B 75 }

hmWanMbus1BVIF23		OBJECT-TYPE
			SYNTAX	INTEGER
			MAX-ACCESS	read-only
			STATUS	current
			::= { hmWanMbus1B 76 }

hmWanMbus1BValue23		OBJECT-TYPE
			SYNTAX	INTEGER
			MAX-ACCESS	read-only
			STATUS	current
			::= { hmWanMbus1B 77 }

hmWanMbus1BVIF24		OBJECT-TYPE
			SYNTAX	INTEGER
			MAX-ACCESS	read-only
			STATUS	current
			::= { hmWanMbus1B 78 }

hmWanMbus1BValue24		OBJECT-TYPE
			SYNTAX	INTEGER
			MAX-ACCESS	read-only
			STATUS	current
			::= { hmWanMbus1B 79 }

hmWanMbus1BVIF25		OBJECT-TYPE
			SYNTAX	INTEGER
			MAX-ACCESS	read-only
			STATUS	current
			::= { hmWanMbus1B 80 }

hmWanMbus1BValue25		OBJECT-TYPE
			SYNTAX	INTEGER
			MAX-ACCESS	read-only
			STATUS	current
			::= { hmWanMbus1B 81 }

hmWanMbus1BVIF26		OBJECT-TYPE
			SYNTAX	INTEGER
			MAX-ACCESS	read-only
			STATUS	current
			::= { hmWanMbus1B 82 }

hmWanMbus1BValue26		OBJECT-TYPE
			SYNTAX	INTEGER
			MAX-ACCESS	read-only
			STATUS	current
			::= { hmWanMbus1B 83 }

hmWanMbus1BVIF27		OBJECT-TYPE
			SYNTAX	INTEGER
			MAX-ACCESS	read-only
			STATUS	current
			::= { hmWanMbus1B 84 }

hmWanMbus1BValue27		OBJECT-TYPE
			SYNTAX	INTEGER
			MAX-ACCESS	read-only
			STATUS	current
			::= { hmWanMbus1B 85 }

hmWanMbus1BVIF28		OBJECT-TYPE
			SYNTAX	INTEGER
			MAX-ACCESS	read-only
			STATUS	current
			::= { hmWanMbus1B 86 }

hmWanMbus1BValue28		OBJECT-TYPE
			SYNTAX	INTEGER
			MAX-ACCESS	read-only
			STATUS	current
			::= { hmWanMbus1B 87 }

hmWanMbus1BVIF29		OBJECT-TYPE
			SYNTAX	INTEGER
			MAX-ACCESS	read-only
			STATUS	current
			::= { hmWanMbus1B 88 }

hmWanMbus1BValue29		OBJECT-TYPE
			SYNTAX	INTEGER
			MAX-ACCESS	read-only
			STATUS	current
			::= { hmWanMbus1B 89 }

hmWanMbus1BVIF2A		OBJECT-TYPE
			SYNTAX	INTEGER
			MAX-ACCESS	read-only
			STATUS	current
			::= { hmWanMbus1B 90 }

hmWanMbus1BValue2A		OBJECT-TYPE
			SYNTAX	INTEGER
			MAX-ACCESS	read-only
			STATUS	current
			::= { hmWanMbus1B 91 }

hmWanMbus1BVIF2B		OBJECT-TYPE
			SYNTAX	INTEGER
			MAX-ACCESS	read-only
			STATUS	current
			::= { hmWanMbus1B 92 }

hmWanMbus1BValue2B		OBJECT-TYPE
			SYNTAX	INTEGER
			MAX-ACCESS	read-only
			STATUS	current
			::= { hmWanMbus1B 93 }

hmWanMbus1BVIF2C		OBJECT-TYPE
			SYNTAX	INTEGER
			MAX-ACCESS	read-only
			STATUS	current
			::= { hmWanMbus1B 94 }

hmWanMbus1BValue2C		OBJECT-TYPE
			SYNTAX	INTEGER
			MAX-ACCESS	read-only
			STATUS	current
			::= { hmWanMbus1B 95 }

hmWanMbus1BVIF2D		OBJECT-TYPE
			SYNTAX	INTEGER
			MAX-ACCESS	read-only
			STATUS	current
			::= { hmWanMbus1B 96 }

hmWanMbus1BValue2D		OBJECT-TYPE
			SYNTAX	INTEGER
			MAX-ACCESS	read-only
			STATUS	current
			::= { hmWanMbus1B 97 }

hmWanMbus1BVIF2E		OBJECT-TYPE
			SYNTAX	INTEGER
			MAX-ACCESS	read-only
			STATUS	current
			::= { hmWanMbus1B 98 }

hmWanMbus1BValue2E		OBJECT-TYPE
			SYNTAX	INTEGER
			MAX-ACCESS	read-only
			STATUS	current
			::= { hmWanMbus1B 99 }

hmWanMbus1BVIF2F		OBJECT-TYPE
			SYNTAX	INTEGER
			MAX-ACCESS	read-only
			STATUS	current
			::= { hmWanMbus1B 100 }

hmWanMbus1BValue2F		OBJECT-TYPE
			SYNTAX	INTEGER
			MAX-ACCESS	read-only
			STATUS	current
			::= { hmWanMbus1B 101 }

hmWanMbus1C			OBJECT IDENTIFIER ::= { hmWanMbus 28 }

hmWanMbus1CIdNumber		OBJECT-TYPE
			SYNTAX	Gauge32
			MAX-ACCESS	read-only
			STATUS	current
			::= { hmWanMbus1C 1 }

hmWanMbus1CManufacturer	OBJECT-TYPE
			SYNTAX	Gauge32
			MAX-ACCESS	read-only
			STATUS	current
			::= { hmWanMbus1C 2 }

hmWanMbus1CVersion		OBJECT-TYPE
			SYNTAX	Gauge32
			MAX-ACCESS	read-only
			STATUS	current
			::= { hmWanMbus1C 3 }

hmWanMbus1CMedium		OBJECT-TYPE
			SYNTAX	Gauge32
			MAX-ACCESS	read-only
			STATUS	current
			::= { hmWanMbus1C 4 }

hmWanMbus1CStatus		OBJECT-TYPE
			SYNTAX	Gauge32
			MAX-ACCESS	read-only
			STATUS	current
			::= { hmWanMbus1C 5 }

hmWanMbus1CVIF00		OBJECT-TYPE
			SYNTAX	INTEGER
			MAX-ACCESS	read-only
			STATUS	current
			::= { hmWanMbus1C 6 }

hmWanMbus1CValue00		OBJECT-TYPE
			SYNTAX	INTEGER
			MAX-ACCESS	read-only
			STATUS	current
			::= { hmWanMbus1C 7 }

hmWanMbus1CVIF01		OBJECT-TYPE
			SYNTAX	INTEGER
			MAX-ACCESS	read-only
			STATUS	current
			::= { hmWanMbus1C 8 }

hmWanMbus1CValue01		OBJECT-TYPE
			SYNTAX	INTEGER
			MAX-ACCESS	read-only
			STATUS	current
			::= { hmWanMbus1C 9 }

hmWanMbus1CVIF02		OBJECT-TYPE
			SYNTAX	INTEGER
			MAX-ACCESS	read-only
			STATUS	current
			::= { hmWanMbus1C 10 }

hmWanMbus1CValue02		OBJECT-TYPE
			SYNTAX	INTEGER
			MAX-ACCESS	read-only
			STATUS	current
			::= { hmWanMbus1C 11 }

hmWanMbus1CVIF03		OBJECT-TYPE
			SYNTAX	INTEGER
			MAX-ACCESS	read-only
			STATUS	current
			::= { hmWanMbus1C 12 }

hmWanMbus1CValue03		OBJECT-TYPE
			SYNTAX	INTEGER
			MAX-ACCESS	read-only
			STATUS	current
			::= { hmWanMbus1C 13 }

hmWanMbus1CVIF04		OBJECT-TYPE
			SYNTAX	INTEGER
			MAX-ACCESS	read-only
			STATUS	current
			::= { hmWanMbus1C 14 }

hmWanMbus1CValue04		OBJECT-TYPE
			SYNTAX	INTEGER
			MAX-ACCESS	read-only
			STATUS	current
			::= { hmWanMbus1C 15 }

hmWanMbus1CVIF05		OBJECT-TYPE
			SYNTAX	INTEGER
			MAX-ACCESS	read-only
			STATUS	current
			::= { hmWanMbus1C 16 }

hmWanMbus1CValue05		OBJECT-TYPE
			SYNTAX	INTEGER
			MAX-ACCESS	read-only
			STATUS	current
			::= { hmWanMbus1C 17 }

hmWanMbus1CVIF06		OBJECT-TYPE
			SYNTAX	INTEGER
			MAX-ACCESS	read-only
			STATUS	current
			::= { hmWanMbus1C 18 }

hmWanMbus1CValue06		OBJECT-TYPE
			SYNTAX	INTEGER
			MAX-ACCESS	read-only
			STATUS	current
			::= { hmWanMbus1C 19 }

hmWanMbus1CVIF07		OBJECT-TYPE
			SYNTAX	INTEGER
			MAX-ACCESS	read-only
			STATUS	current
			::= { hmWanMbus1C 20 }

hmWanMbus1CValue07		OBJECT-TYPE
			SYNTAX	INTEGER
			MAX-ACCESS	read-only
			STATUS	current
			::= { hmWanMbus1C 21 }

hmWanMbus1CVIF08		OBJECT-TYPE
			SYNTAX	INTEGER
			MAX-ACCESS	read-only
			STATUS	current
			::= { hmWanMbus1C 22 }

hmWanMbus1CValue08		OBJECT-TYPE
			SYNTAX	INTEGER
			MAX-ACCESS	read-only
			STATUS	current
			::= { hmWanMbus1C 23 }

hmWanMbus1CVIF09		OBJECT-TYPE
			SYNTAX	INTEGER
			MAX-ACCESS	read-only
			STATUS	current
			::= { hmWanMbus1C 24 }

hmWanMbus1CValue09		OBJECT-TYPE
			SYNTAX	INTEGER
			MAX-ACCESS	read-only
			STATUS	current
			::= { hmWanMbus1C 25 }

hmWanMbus1CVIF0A		OBJECT-TYPE
			SYNTAX	INTEGER
			MAX-ACCESS	read-only
			STATUS	current
			::= { hmWanMbus1C 26 }

hmWanMbus1CValue0A		OBJECT-TYPE
			SYNTAX	INTEGER
			MAX-ACCESS	read-only
			STATUS	current
			::= { hmWanMbus1C 27 }

hmWanMbus1CVIF0B		OBJECT-TYPE
			SYNTAX	INTEGER
			MAX-ACCESS	read-only
			STATUS	current
			::= { hmWanMbus1C 28 }

hmWanMbus1CValue0B		OBJECT-TYPE
			SYNTAX	INTEGER
			MAX-ACCESS	read-only
			STATUS	current
			::= { hmWanMbus1C 29 }

hmWanMbus1CVIF0C		OBJECT-TYPE
			SYNTAX	INTEGER
			MAX-ACCESS	read-only
			STATUS	current
			::= { hmWanMbus1C 30 }

hmWanMbus1CValue0C		OBJECT-TYPE
			SYNTAX	INTEGER
			MAX-ACCESS	read-only
			STATUS	current
			::= { hmWanMbus1C 31 }

hmWanMbus1CVIF0D		OBJECT-TYPE
			SYNTAX	INTEGER
			MAX-ACCESS	read-only
			STATUS	current
			::= { hmWanMbus1C 32 }

hmWanMbus1CValue0D		OBJECT-TYPE
			SYNTAX	INTEGER
			MAX-ACCESS	read-only
			STATUS	current
			::= { hmWanMbus1C 33 }

hmWanMbus1CVIF0E		OBJECT-TYPE
			SYNTAX	INTEGER
			MAX-ACCESS	read-only
			STATUS	current
			::= { hmWanMbus1C 34 }

hmWanMbus1CValue0E		OBJECT-TYPE
			SYNTAX	INTEGER
			MAX-ACCESS	read-only
			STATUS	current
			::= { hmWanMbus1C 35 }

hmWanMbus1CVIF0F		OBJECT-TYPE
			SYNTAX	INTEGER
			MAX-ACCESS	read-only
			STATUS	current
			::= { hmWanMbus1C 36 }

hmWanMbus1CValue0F		OBJECT-TYPE
			SYNTAX	INTEGER
			MAX-ACCESS	read-only
			STATUS	current
			::= { hmWanMbus1C 37 }

hmWanMbus1CVIF10		OBJECT-TYPE
			SYNTAX	INTEGER
			MAX-ACCESS	read-only
			STATUS	current
			::= { hmWanMbus1C 38 }

hmWanMbus1CValue10		OBJECT-TYPE
			SYNTAX	INTEGER
			MAX-ACCESS	read-only
			STATUS	current
			::= { hmWanMbus1C 39 }

hmWanMbus1CVIF11		OBJECT-TYPE
			SYNTAX	INTEGER
			MAX-ACCESS	read-only
			STATUS	current
			::= { hmWanMbus1C 40 }

hmWanMbus1CValue11		OBJECT-TYPE
			SYNTAX	INTEGER
			MAX-ACCESS	read-only
			STATUS	current
			::= { hmWanMbus1C 41 }

hmWanMbus1CVIF12		OBJECT-TYPE
			SYNTAX	INTEGER
			MAX-ACCESS	read-only
			STATUS	current
			::= { hmWanMbus1C 42 }

hmWanMbus1CValue12		OBJECT-TYPE
			SYNTAX	INTEGER
			MAX-ACCESS	read-only
			STATUS	current
			::= { hmWanMbus1C 43 }

hmWanMbus1CVIF13		OBJECT-TYPE
			SYNTAX	INTEGER
			MAX-ACCESS	read-only
			STATUS	current
			::= { hmWanMbus1C 44 }

hmWanMbus1CValue13		OBJECT-TYPE
			SYNTAX	INTEGER
			MAX-ACCESS	read-only
			STATUS	current
			::= { hmWanMbus1C 45 }

hmWanMbus1CVIF14		OBJECT-TYPE
			SYNTAX	INTEGER
			MAX-ACCESS	read-only
			STATUS	current
			::= { hmWanMbus1C 46 }

hmWanMbus1CValue14		OBJECT-TYPE
			SYNTAX	INTEGER
			MAX-ACCESS	read-only
			STATUS	current
			::= { hmWanMbus1C 47 }

hmWanMbus1CVIF15		OBJECT-TYPE
			SYNTAX	INTEGER
			MAX-ACCESS	read-only
			STATUS	current
			::= { hmWanMbus1C 48 }

hmWanMbus1CValue15		OBJECT-TYPE
			SYNTAX	INTEGER
			MAX-ACCESS	read-only
			STATUS	current
			::= { hmWanMbus1C 49 }

hmWanMbus1CVIF16		OBJECT-TYPE
			SYNTAX	INTEGER
			MAX-ACCESS	read-only
			STATUS	current
			::= { hmWanMbus1C 50 }

hmWanMbus1CValue16		OBJECT-TYPE
			SYNTAX	INTEGER
			MAX-ACCESS	read-only
			STATUS	current
			::= { hmWanMbus1C 51 }

hmWanMbus1CVIF17		OBJECT-TYPE
			SYNTAX	INTEGER
			MAX-ACCESS	read-only
			STATUS	current
			::= { hmWanMbus1C 52 }

hmWanMbus1CValue17		OBJECT-TYPE
			SYNTAX	INTEGER
			MAX-ACCESS	read-only
			STATUS	current
			::= { hmWanMbus1C 53 }

hmWanMbus1CVIF18		OBJECT-TYPE
			SYNTAX	INTEGER
			MAX-ACCESS	read-only
			STATUS	current
			::= { hmWanMbus1C 54 }

hmWanMbus1CValue18		OBJECT-TYPE
			SYNTAX	INTEGER
			MAX-ACCESS	read-only
			STATUS	current
			::= { hmWanMbus1C 55 }

hmWanMbus1CVIF19		OBJECT-TYPE
			SYNTAX	INTEGER
			MAX-ACCESS	read-only
			STATUS	current
			::= { hmWanMbus1C 56 }

hmWanMbus1CValue19		OBJECT-TYPE
			SYNTAX	INTEGER
			MAX-ACCESS	read-only
			STATUS	current
			::= { hmWanMbus1C 57 }

hmWanMbus1CVIF1A		OBJECT-TYPE
			SYNTAX	INTEGER
			MAX-ACCESS	read-only
			STATUS	current
			::= { hmWanMbus1C 58 }

hmWanMbus1CValue1A		OBJECT-TYPE
			SYNTAX	INTEGER
			MAX-ACCESS	read-only
			STATUS	current
			::= { hmWanMbus1C 59 }

hmWanMbus1CVIF1B		OBJECT-TYPE
			SYNTAX	INTEGER
			MAX-ACCESS	read-only
			STATUS	current
			::= { hmWanMbus1C 60 }

hmWanMbus1CValue1B		OBJECT-TYPE
			SYNTAX	INTEGER
			MAX-ACCESS	read-only
			STATUS	current
			::= { hmWanMbus1C 61 }

hmWanMbus1CVIF1C		OBJECT-TYPE
			SYNTAX	INTEGER
			MAX-ACCESS	read-only
			STATUS	current
			::= { hmWanMbus1C 62 }

hmWanMbus1CValue1C		OBJECT-TYPE
			SYNTAX	INTEGER
			MAX-ACCESS	read-only
			STATUS	current
			::= { hmWanMbus1C 63 }

hmWanMbus1CVIF1D		OBJECT-TYPE
			SYNTAX	INTEGER
			MAX-ACCESS	read-only
			STATUS	current
			::= { hmWanMbus1C 64 }

hmWanMbus1CValue1D		OBJECT-TYPE
			SYNTAX	INTEGER
			MAX-ACCESS	read-only
			STATUS	current
			::= { hmWanMbus1C 65 }

hmWanMbus1CVIF1E		OBJECT-TYPE
			SYNTAX	INTEGER
			MAX-ACCESS	read-only
			STATUS	current
			::= { hmWanMbus1C 66 }

hmWanMbus1CValue1E		OBJECT-TYPE
			SYNTAX	INTEGER
			MAX-ACCESS	read-only
			STATUS	current
			::= { hmWanMbus1C 67 }

hmWanMbus1CVIF1F		OBJECT-TYPE
			SYNTAX	INTEGER
			MAX-ACCESS	read-only
			STATUS	current
			::= { hmWanMbus1C 68 }

hmWanMbus1CValue1F		OBJECT-TYPE
			SYNTAX	INTEGER
			MAX-ACCESS	read-only
			STATUS	current
			::= { hmWanMbus1C 69 }

hmWanMbus1CVIF20		OBJECT-TYPE
			SYNTAX	INTEGER
			MAX-ACCESS	read-only
			STATUS	current
			::= { hmWanMbus1C 70 }

hmWanMbus1CValue20		OBJECT-TYPE
			SYNTAX	INTEGER
			MAX-ACCESS	read-only
			STATUS	current
			::= { hmWanMbus1C 71 }

hmWanMbus1CVIF21		OBJECT-TYPE
			SYNTAX	INTEGER
			MAX-ACCESS	read-only
			STATUS	current
			::= { hmWanMbus1C 72 }

hmWanMbus1CValue21		OBJECT-TYPE
			SYNTAX	INTEGER
			MAX-ACCESS	read-only
			STATUS	current
			::= { hmWanMbus1C 73 }

hmWanMbus1CVIF22		OBJECT-TYPE
			SYNTAX	INTEGER
			MAX-ACCESS	read-only
			STATUS	current
			::= { hmWanMbus1C 74 }

hmWanMbus1CValue22		OBJECT-TYPE
			SYNTAX	INTEGER
			MAX-ACCESS	read-only
			STATUS	current
			::= { hmWanMbus1C 75 }

hmWanMbus1CVIF23		OBJECT-TYPE
			SYNTAX	INTEGER
			MAX-ACCESS	read-only
			STATUS	current
			::= { hmWanMbus1C 76 }

hmWanMbus1CValue23		OBJECT-TYPE
			SYNTAX	INTEGER
			MAX-ACCESS	read-only
			STATUS	current
			::= { hmWanMbus1C 77 }

hmWanMbus1CVIF24		OBJECT-TYPE
			SYNTAX	INTEGER
			MAX-ACCESS	read-only
			STATUS	current
			::= { hmWanMbus1C 78 }

hmWanMbus1CValue24		OBJECT-TYPE
			SYNTAX	INTEGER
			MAX-ACCESS	read-only
			STATUS	current
			::= { hmWanMbus1C 79 }

hmWanMbus1CVIF25		OBJECT-TYPE
			SYNTAX	INTEGER
			MAX-ACCESS	read-only
			STATUS	current
			::= { hmWanMbus1C 80 }

hmWanMbus1CValue25		OBJECT-TYPE
			SYNTAX	INTEGER
			MAX-ACCESS	read-only
			STATUS	current
			::= { hmWanMbus1C 81 }

hmWanMbus1CVIF26		OBJECT-TYPE
			SYNTAX	INTEGER
			MAX-ACCESS	read-only
			STATUS	current
			::= { hmWanMbus1C 82 }

hmWanMbus1CValue26		OBJECT-TYPE
			SYNTAX	INTEGER
			MAX-ACCESS	read-only
			STATUS	current
			::= { hmWanMbus1C 83 }

hmWanMbus1CVIF27		OBJECT-TYPE
			SYNTAX	INTEGER
			MAX-ACCESS	read-only
			STATUS	current
			::= { hmWanMbus1C 84 }

hmWanMbus1CValue27		OBJECT-TYPE
			SYNTAX	INTEGER
			MAX-ACCESS	read-only
			STATUS	current
			::= { hmWanMbus1C 85 }

hmWanMbus1CVIF28		OBJECT-TYPE
			SYNTAX	INTEGER
			MAX-ACCESS	read-only
			STATUS	current
			::= { hmWanMbus1C 86 }

hmWanMbus1CValue28		OBJECT-TYPE
			SYNTAX	INTEGER
			MAX-ACCESS	read-only
			STATUS	current
			::= { hmWanMbus1C 87 }

hmWanMbus1CVIF29		OBJECT-TYPE
			SYNTAX	INTEGER
			MAX-ACCESS	read-only
			STATUS	current
			::= { hmWanMbus1C 88 }

hmWanMbus1CValue29		OBJECT-TYPE
			SYNTAX	INTEGER
			MAX-ACCESS	read-only
			STATUS	current
			::= { hmWanMbus1C 89 }

hmWanMbus1CVIF2A		OBJECT-TYPE
			SYNTAX	INTEGER
			MAX-ACCESS	read-only
			STATUS	current
			::= { hmWanMbus1C 90 }

hmWanMbus1CValue2A		OBJECT-TYPE
			SYNTAX	INTEGER
			MAX-ACCESS	read-only
			STATUS	current
			::= { hmWanMbus1C 91 }

hmWanMbus1CVIF2B		OBJECT-TYPE
			SYNTAX	INTEGER
			MAX-ACCESS	read-only
			STATUS	current
			::= { hmWanMbus1C 92 }

hmWanMbus1CValue2B		OBJECT-TYPE
			SYNTAX	INTEGER
			MAX-ACCESS	read-only
			STATUS	current
			::= { hmWanMbus1C 93 }

hmWanMbus1CVIF2C		OBJECT-TYPE
			SYNTAX	INTEGER
			MAX-ACCESS	read-only
			STATUS	current
			::= { hmWanMbus1C 94 }

hmWanMbus1CValue2C		OBJECT-TYPE
			SYNTAX	INTEGER
			MAX-ACCESS	read-only
			STATUS	current
			::= { hmWanMbus1C 95 }

hmWanMbus1CVIF2D		OBJECT-TYPE
			SYNTAX	INTEGER
			MAX-ACCESS	read-only
			STATUS	current
			::= { hmWanMbus1C 96 }

hmWanMbus1CValue2D		OBJECT-TYPE
			SYNTAX	INTEGER
			MAX-ACCESS	read-only
			STATUS	current
			::= { hmWanMbus1C 97 }

hmWanMbus1CVIF2E		OBJECT-TYPE
			SYNTAX	INTEGER
			MAX-ACCESS	read-only
			STATUS	current
			::= { hmWanMbus1C 98 }

hmWanMbus1CValue2E		OBJECT-TYPE
			SYNTAX	INTEGER
			MAX-ACCESS	read-only
			STATUS	current
			::= { hmWanMbus1C 99 }

hmWanMbus1CVIF2F		OBJECT-TYPE
			SYNTAX	INTEGER
			MAX-ACCESS	read-only
			STATUS	current
			::= { hmWanMbus1C 100 }

hmWanMbus1CValue2F		OBJECT-TYPE
			SYNTAX	INTEGER
			MAX-ACCESS	read-only
			STATUS	current
			::= { hmWanMbus1C 101 }

hmWanMbus1D			OBJECT IDENTIFIER ::= { hmWanMbus 29 }

hmWanMbus1DIdNumber		OBJECT-TYPE
			SYNTAX	Gauge32
			MAX-ACCESS	read-only
			STATUS	current
			::= { hmWanMbus1D 1 }

hmWanMbus1DManufacturer	OBJECT-TYPE
			SYNTAX	Gauge32
			MAX-ACCESS	read-only
			STATUS	current
			::= { hmWanMbus1D 2 }

hmWanMbus1DVersion		OBJECT-TYPE
			SYNTAX	Gauge32
			MAX-ACCESS	read-only
			STATUS	current
			::= { hmWanMbus1D 3 }

hmWanMbus1DMedium		OBJECT-TYPE
			SYNTAX	Gauge32
			MAX-ACCESS	read-only
			STATUS	current
			::= { hmWanMbus1D 4 }

hmWanMbus1DStatus		OBJECT-TYPE
			SYNTAX	Gauge32
			MAX-ACCESS	read-only
			STATUS	current
			::= { hmWanMbus1D 5 }

hmWanMbus1DVIF00		OBJECT-TYPE
			SYNTAX	INTEGER
			MAX-ACCESS	read-only
			STATUS	current
			::= { hmWanMbus1D 6 }

hmWanMbus1DValue00		OBJECT-TYPE
			SYNTAX	INTEGER
			MAX-ACCESS	read-only
			STATUS	current
			::= { hmWanMbus1D 7 }

hmWanMbus1DVIF01		OBJECT-TYPE
			SYNTAX	INTEGER
			MAX-ACCESS	read-only
			STATUS	current
			::= { hmWanMbus1D 8 }

hmWanMbus1DValue01		OBJECT-TYPE
			SYNTAX	INTEGER
			MAX-ACCESS	read-only
			STATUS	current
			::= { hmWanMbus1D 9 }

hmWanMbus1DVIF02		OBJECT-TYPE
			SYNTAX	INTEGER
			MAX-ACCESS	read-only
			STATUS	current
			::= { hmWanMbus1D 10 }

hmWanMbus1DValue02		OBJECT-TYPE
			SYNTAX	INTEGER
			MAX-ACCESS	read-only
			STATUS	current
			::= { hmWanMbus1D 11 }

hmWanMbus1DVIF03		OBJECT-TYPE
			SYNTAX	INTEGER
			MAX-ACCESS	read-only
			STATUS	current
			::= { hmWanMbus1D 12 }

hmWanMbus1DValue03		OBJECT-TYPE
			SYNTAX	INTEGER
			MAX-ACCESS	read-only
			STATUS	current
			::= { hmWanMbus1D 13 }

hmWanMbus1DVIF04		OBJECT-TYPE
			SYNTAX	INTEGER
			MAX-ACCESS	read-only
			STATUS	current
			::= { hmWanMbus1D 14 }

hmWanMbus1DValue04		OBJECT-TYPE
			SYNTAX	INTEGER
			MAX-ACCESS	read-only
			STATUS	current
			::= { hmWanMbus1D 15 }

hmWanMbus1DVIF05		OBJECT-TYPE
			SYNTAX	INTEGER
			MAX-ACCESS	read-only
			STATUS	current
			::= { hmWanMbus1D 16 }

hmWanMbus1DValue05		OBJECT-TYPE
			SYNTAX	INTEGER
			MAX-ACCESS	read-only
			STATUS	current
			::= { hmWanMbus1D 17 }

hmWanMbus1DVIF06		OBJECT-TYPE
			SYNTAX	INTEGER
			MAX-ACCESS	read-only
			STATUS	current
			::= { hmWanMbus1D 18 }

hmWanMbus1DValue06		OBJECT-TYPE
			SYNTAX	INTEGER
			MAX-ACCESS	read-only
			STATUS	current
			::= { hmWanMbus1D 19 }

hmWanMbus1DVIF07		OBJECT-TYPE
			SYNTAX	INTEGER
			MAX-ACCESS	read-only
			STATUS	current
			::= { hmWanMbus1D 20 }

hmWanMbus1DValue07		OBJECT-TYPE
			SYNTAX	INTEGER
			MAX-ACCESS	read-only
			STATUS	current
			::= { hmWanMbus1D 21 }

hmWanMbus1DVIF08		OBJECT-TYPE
			SYNTAX	INTEGER
			MAX-ACCESS	read-only
			STATUS	current
			::= { hmWanMbus1D 22 }

hmWanMbus1DValue08		OBJECT-TYPE
			SYNTAX	INTEGER
			MAX-ACCESS	read-only
			STATUS	current
			::= { hmWanMbus1D 23 }

hmWanMbus1DVIF09		OBJECT-TYPE
			SYNTAX	INTEGER
			MAX-ACCESS	read-only
			STATUS	current
			::= { hmWanMbus1D 24 }

hmWanMbus1DValue09		OBJECT-TYPE
			SYNTAX	INTEGER
			MAX-ACCESS	read-only
			STATUS	current
			::= { hmWanMbus1D 25 }

hmWanMbus1DVIF0A		OBJECT-TYPE
			SYNTAX	INTEGER
			MAX-ACCESS	read-only
			STATUS	current
			::= { hmWanMbus1D 26 }

hmWanMbus1DValue0A		OBJECT-TYPE
			SYNTAX	INTEGER
			MAX-ACCESS	read-only
			STATUS	current
			::= { hmWanMbus1D 27 }

hmWanMbus1DVIF0B		OBJECT-TYPE
			SYNTAX	INTEGER
			MAX-ACCESS	read-only
			STATUS	current
			::= { hmWanMbus1D 28 }

hmWanMbus1DValue0B		OBJECT-TYPE
			SYNTAX	INTEGER
			MAX-ACCESS	read-only
			STATUS	current
			::= { hmWanMbus1D 29 }

hmWanMbus1DVIF0C		OBJECT-TYPE
			SYNTAX	INTEGER
			MAX-ACCESS	read-only
			STATUS	current
			::= { hmWanMbus1D 30 }

hmWanMbus1DValue0C		OBJECT-TYPE
			SYNTAX	INTEGER
			MAX-ACCESS	read-only
			STATUS	current
			::= { hmWanMbus1D 31 }

hmWanMbus1DVIF0D		OBJECT-TYPE
			SYNTAX	INTEGER
			MAX-ACCESS	read-only
			STATUS	current
			::= { hmWanMbus1D 32 }

hmWanMbus1DValue0D		OBJECT-TYPE
			SYNTAX	INTEGER
			MAX-ACCESS	read-only
			STATUS	current
			::= { hmWanMbus1D 33 }

hmWanMbus1DVIF0E		OBJECT-TYPE
			SYNTAX	INTEGER
			MAX-ACCESS	read-only
			STATUS	current
			::= { hmWanMbus1D 34 }

hmWanMbus1DValue0E		OBJECT-TYPE
			SYNTAX	INTEGER
			MAX-ACCESS	read-only
			STATUS	current
			::= { hmWanMbus1D 35 }

hmWanMbus1DVIF0F		OBJECT-TYPE
			SYNTAX	INTEGER
			MAX-ACCESS	read-only
			STATUS	current
			::= { hmWanMbus1D 36 }

hmWanMbus1DValue0F		OBJECT-TYPE
			SYNTAX	INTEGER
			MAX-ACCESS	read-only
			STATUS	current
			::= { hmWanMbus1D 37 }

hmWanMbus1DVIF10		OBJECT-TYPE
			SYNTAX	INTEGER
			MAX-ACCESS	read-only
			STATUS	current
			::= { hmWanMbus1D 38 }

hmWanMbus1DValue10		OBJECT-TYPE
			SYNTAX	INTEGER
			MAX-ACCESS	read-only
			STATUS	current
			::= { hmWanMbus1D 39 }

hmWanMbus1DVIF11		OBJECT-TYPE
			SYNTAX	INTEGER
			MAX-ACCESS	read-only
			STATUS	current
			::= { hmWanMbus1D 40 }

hmWanMbus1DValue11		OBJECT-TYPE
			SYNTAX	INTEGER
			MAX-ACCESS	read-only
			STATUS	current
			::= { hmWanMbus1D 41 }

hmWanMbus1DVIF12		OBJECT-TYPE
			SYNTAX	INTEGER
			MAX-ACCESS	read-only
			STATUS	current
			::= { hmWanMbus1D 42 }

hmWanMbus1DValue12		OBJECT-TYPE
			SYNTAX	INTEGER
			MAX-ACCESS	read-only
			STATUS	current
			::= { hmWanMbus1D 43 }

hmWanMbus1DVIF13		OBJECT-TYPE
			SYNTAX	INTEGER
			MAX-ACCESS	read-only
			STATUS	current
			::= { hmWanMbus1D 44 }

hmWanMbus1DValue13		OBJECT-TYPE
			SYNTAX	INTEGER
			MAX-ACCESS	read-only
			STATUS	current
			::= { hmWanMbus1D 45 }

hmWanMbus1DVIF14		OBJECT-TYPE
			SYNTAX	INTEGER
			MAX-ACCESS	read-only
			STATUS	current
			::= { hmWanMbus1D 46 }

hmWanMbus1DValue14		OBJECT-TYPE
			SYNTAX	INTEGER
			MAX-ACCESS	read-only
			STATUS	current
			::= { hmWanMbus1D 47 }

hmWanMbus1DVIF15		OBJECT-TYPE
			SYNTAX	INTEGER
			MAX-ACCESS	read-only
			STATUS	current
			::= { hmWanMbus1D 48 }

hmWanMbus1DValue15		OBJECT-TYPE
			SYNTAX	INTEGER
			MAX-ACCESS	read-only
			STATUS	current
			::= { hmWanMbus1D 49 }

hmWanMbus1DVIF16		OBJECT-TYPE
			SYNTAX	INTEGER
			MAX-ACCESS	read-only
			STATUS	current
			::= { hmWanMbus1D 50 }

hmWanMbus1DValue16		OBJECT-TYPE
			SYNTAX	INTEGER
			MAX-ACCESS	read-only
			STATUS	current
			::= { hmWanMbus1D 51 }

hmWanMbus1DVIF17		OBJECT-TYPE
			SYNTAX	INTEGER
			MAX-ACCESS	read-only
			STATUS	current
			::= { hmWanMbus1D 52 }

hmWanMbus1DValue17		OBJECT-TYPE
			SYNTAX	INTEGER
			MAX-ACCESS	read-only
			STATUS	current
			::= { hmWanMbus1D 53 }

hmWanMbus1DVIF18		OBJECT-TYPE
			SYNTAX	INTEGER
			MAX-ACCESS	read-only
			STATUS	current
			::= { hmWanMbus1D 54 }

hmWanMbus1DValue18		OBJECT-TYPE
			SYNTAX	INTEGER
			MAX-ACCESS	read-only
			STATUS	current
			::= { hmWanMbus1D 55 }

hmWanMbus1DVIF19		OBJECT-TYPE
			SYNTAX	INTEGER
			MAX-ACCESS	read-only
			STATUS	current
			::= { hmWanMbus1D 56 }

hmWanMbus1DValue19		OBJECT-TYPE
			SYNTAX	INTEGER
			MAX-ACCESS	read-only
			STATUS	current
			::= { hmWanMbus1D 57 }

hmWanMbus1DVIF1A		OBJECT-TYPE
			SYNTAX	INTEGER
			MAX-ACCESS	read-only
			STATUS	current
			::= { hmWanMbus1D 58 }

hmWanMbus1DValue1A		OBJECT-TYPE
			SYNTAX	INTEGER
			MAX-ACCESS	read-only
			STATUS	current
			::= { hmWanMbus1D 59 }

hmWanMbus1DVIF1B		OBJECT-TYPE
			SYNTAX	INTEGER
			MAX-ACCESS	read-only
			STATUS	current
			::= { hmWanMbus1D 60 }

hmWanMbus1DValue1B		OBJECT-TYPE
			SYNTAX	INTEGER
			MAX-ACCESS	read-only
			STATUS	current
			::= { hmWanMbus1D 61 }

hmWanMbus1DVIF1C		OBJECT-TYPE
			SYNTAX	INTEGER
			MAX-ACCESS	read-only
			STATUS	current
			::= { hmWanMbus1D 62 }

hmWanMbus1DValue1C		OBJECT-TYPE
			SYNTAX	INTEGER
			MAX-ACCESS	read-only
			STATUS	current
			::= { hmWanMbus1D 63 }

hmWanMbus1DVIF1D		OBJECT-TYPE
			SYNTAX	INTEGER
			MAX-ACCESS	read-only
			STATUS	current
			::= { hmWanMbus1D 64 }

hmWanMbus1DValue1D		OBJECT-TYPE
			SYNTAX	INTEGER
			MAX-ACCESS	read-only
			STATUS	current
			::= { hmWanMbus1D 65 }

hmWanMbus1DVIF1E		OBJECT-TYPE
			SYNTAX	INTEGER
			MAX-ACCESS	read-only
			STATUS	current
			::= { hmWanMbus1D 66 }

hmWanMbus1DValue1E		OBJECT-TYPE
			SYNTAX	INTEGER
			MAX-ACCESS	read-only
			STATUS	current
			::= { hmWanMbus1D 67 }

hmWanMbus1DVIF1F		OBJECT-TYPE
			SYNTAX	INTEGER
			MAX-ACCESS	read-only
			STATUS	current
			::= { hmWanMbus1D 68 }

hmWanMbus1DValue1F		OBJECT-TYPE
			SYNTAX	INTEGER
			MAX-ACCESS	read-only
			STATUS	current
			::= { hmWanMbus1D 69 }

hmWanMbus1DVIF20		OBJECT-TYPE
			SYNTAX	INTEGER
			MAX-ACCESS	read-only
			STATUS	current
			::= { hmWanMbus1D 70 }

hmWanMbus1DValue20		OBJECT-TYPE
			SYNTAX	INTEGER
			MAX-ACCESS	read-only
			STATUS	current
			::= { hmWanMbus1D 71 }

hmWanMbus1DVIF21		OBJECT-TYPE
			SYNTAX	INTEGER
			MAX-ACCESS	read-only
			STATUS	current
			::= { hmWanMbus1D 72 }

hmWanMbus1DValue21		OBJECT-TYPE
			SYNTAX	INTEGER
			MAX-ACCESS	read-only
			STATUS	current
			::= { hmWanMbus1D 73 }

hmWanMbus1DVIF22		OBJECT-TYPE
			SYNTAX	INTEGER
			MAX-ACCESS	read-only
			STATUS	current
			::= { hmWanMbus1D 74 }

hmWanMbus1DValue22		OBJECT-TYPE
			SYNTAX	INTEGER
			MAX-ACCESS	read-only
			STATUS	current
			::= { hmWanMbus1D 75 }

hmWanMbus1DVIF23		OBJECT-TYPE
			SYNTAX	INTEGER
			MAX-ACCESS	read-only
			STATUS	current
			::= { hmWanMbus1D 76 }

hmWanMbus1DValue23		OBJECT-TYPE
			SYNTAX	INTEGER
			MAX-ACCESS	read-only
			STATUS	current
			::= { hmWanMbus1D 77 }

hmWanMbus1DVIF24		OBJECT-TYPE
			SYNTAX	INTEGER
			MAX-ACCESS	read-only
			STATUS	current
			::= { hmWanMbus1D 78 }

hmWanMbus1DValue24		OBJECT-TYPE
			SYNTAX	INTEGER
			MAX-ACCESS	read-only
			STATUS	current
			::= { hmWanMbus1D 79 }

hmWanMbus1DVIF25		OBJECT-TYPE
			SYNTAX	INTEGER
			MAX-ACCESS	read-only
			STATUS	current
			::= { hmWanMbus1D 80 }

hmWanMbus1DValue25		OBJECT-TYPE
			SYNTAX	INTEGER
			MAX-ACCESS	read-only
			STATUS	current
			::= { hmWanMbus1D 81 }

hmWanMbus1DVIF26		OBJECT-TYPE
			SYNTAX	INTEGER
			MAX-ACCESS	read-only
			STATUS	current
			::= { hmWanMbus1D 82 }

hmWanMbus1DValue26		OBJECT-TYPE
			SYNTAX	INTEGER
			MAX-ACCESS	read-only
			STATUS	current
			::= { hmWanMbus1D 83 }

hmWanMbus1DVIF27		OBJECT-TYPE
			SYNTAX	INTEGER
			MAX-ACCESS	read-only
			STATUS	current
			::= { hmWanMbus1D 84 }

hmWanMbus1DValue27		OBJECT-TYPE
			SYNTAX	INTEGER
			MAX-ACCESS	read-only
			STATUS	current
			::= { hmWanMbus1D 85 }

hmWanMbus1DVIF28		OBJECT-TYPE
			SYNTAX	INTEGER
			MAX-ACCESS	read-only
			STATUS	current
			::= { hmWanMbus1D 86 }

hmWanMbus1DValue28		OBJECT-TYPE
			SYNTAX	INTEGER
			MAX-ACCESS	read-only
			STATUS	current
			::= { hmWanMbus1D 87 }

hmWanMbus1DVIF29		OBJECT-TYPE
			SYNTAX	INTEGER
			MAX-ACCESS	read-only
			STATUS	current
			::= { hmWanMbus1D 88 }

hmWanMbus1DValue29		OBJECT-TYPE
			SYNTAX	INTEGER
			MAX-ACCESS	read-only
			STATUS	current
			::= { hmWanMbus1D 89 }

hmWanMbus1DVIF2A		OBJECT-TYPE
			SYNTAX	INTEGER
			MAX-ACCESS	read-only
			STATUS	current
			::= { hmWanMbus1D 90 }

hmWanMbus1DValue2A		OBJECT-TYPE
			SYNTAX	INTEGER
			MAX-ACCESS	read-only
			STATUS	current
			::= { hmWanMbus1D 91 }

hmWanMbus1DVIF2B		OBJECT-TYPE
			SYNTAX	INTEGER
			MAX-ACCESS	read-only
			STATUS	current
			::= { hmWanMbus1D 92 }

hmWanMbus1DValue2B		OBJECT-TYPE
			SYNTAX	INTEGER
			MAX-ACCESS	read-only
			STATUS	current
			::= { hmWanMbus1D 93 }

hmWanMbus1DVIF2C		OBJECT-TYPE
			SYNTAX	INTEGER
			MAX-ACCESS	read-only
			STATUS	current
			::= { hmWanMbus1D 94 }

hmWanMbus1DValue2C		OBJECT-TYPE
			SYNTAX	INTEGER
			MAX-ACCESS	read-only
			STATUS	current
			::= { hmWanMbus1D 95 }

hmWanMbus1DVIF2D		OBJECT-TYPE
			SYNTAX	INTEGER
			MAX-ACCESS	read-only
			STATUS	current
			::= { hmWanMbus1D 96 }

hmWanMbus1DValue2D		OBJECT-TYPE
			SYNTAX	INTEGER
			MAX-ACCESS	read-only
			STATUS	current
			::= { hmWanMbus1D 97 }

hmWanMbus1DVIF2E		OBJECT-TYPE
			SYNTAX	INTEGER
			MAX-ACCESS	read-only
			STATUS	current
			::= { hmWanMbus1D 98 }

hmWanMbus1DValue2E		OBJECT-TYPE
			SYNTAX	INTEGER
			MAX-ACCESS	read-only
			STATUS	current
			::= { hmWanMbus1D 99 }

hmWanMbus1DVIF2F		OBJECT-TYPE
			SYNTAX	INTEGER
			MAX-ACCESS	read-only
			STATUS	current
			::= { hmWanMbus1D 100 }

hmWanMbus1DValue2F		OBJECT-TYPE
			SYNTAX	INTEGER
			MAX-ACCESS	read-only
			STATUS	current
			::= { hmWanMbus1D 101 }

hmWanMbus1E			OBJECT IDENTIFIER ::= { hmWanMbus 30 }

hmWanMbus1EIdNumber		OBJECT-TYPE
			SYNTAX	Gauge32
			MAX-ACCESS	read-only
			STATUS	current
			::= { hmWanMbus1E 1 }

hmWanMbus1EManufacturer	OBJECT-TYPE
			SYNTAX	Gauge32
			MAX-ACCESS	read-only
			STATUS	current
			::= { hmWanMbus1E 2 }

hmWanMbus1EVersion		OBJECT-TYPE
			SYNTAX	Gauge32
			MAX-ACCESS	read-only
			STATUS	current
			::= { hmWanMbus1E 3 }

hmWanMbus1EMedium		OBJECT-TYPE
			SYNTAX	Gauge32
			MAX-ACCESS	read-only
			STATUS	current
			::= { hmWanMbus1E 4 }

hmWanMbus1EStatus		OBJECT-TYPE
			SYNTAX	Gauge32
			MAX-ACCESS	read-only
			STATUS	current
			::= { hmWanMbus1E 5 }

hmWanMbus1EVIF00		OBJECT-TYPE
			SYNTAX	INTEGER
			MAX-ACCESS	read-only
			STATUS	current
			::= { hmWanMbus1E 6 }

hmWanMbus1EValue00		OBJECT-TYPE
			SYNTAX	INTEGER
			MAX-ACCESS	read-only
			STATUS	current
			::= { hmWanMbus1E 7 }

hmWanMbus1EVIF01		OBJECT-TYPE
			SYNTAX	INTEGER
			MAX-ACCESS	read-only
			STATUS	current
			::= { hmWanMbus1E 8 }

hmWanMbus1EValue01		OBJECT-TYPE
			SYNTAX	INTEGER
			MAX-ACCESS	read-only
			STATUS	current
			::= { hmWanMbus1E 9 }

hmWanMbus1EVIF02		OBJECT-TYPE
			SYNTAX	INTEGER
			MAX-ACCESS	read-only
			STATUS	current
			::= { hmWanMbus1E 10 }

hmWanMbus1EValue02		OBJECT-TYPE
			SYNTAX	INTEGER
			MAX-ACCESS	read-only
			STATUS	current
			::= { hmWanMbus1E 11 }

hmWanMbus1EVIF03		OBJECT-TYPE
			SYNTAX	INTEGER
			MAX-ACCESS	read-only
			STATUS	current
			::= { hmWanMbus1E 12 }

hmWanMbus1EValue03		OBJECT-TYPE
			SYNTAX	INTEGER
			MAX-ACCESS	read-only
			STATUS	current
			::= { hmWanMbus1E 13 }

hmWanMbus1EVIF04		OBJECT-TYPE
			SYNTAX	INTEGER
			MAX-ACCESS	read-only
			STATUS	current
			::= { hmWanMbus1E 14 }

hmWanMbus1EValue04		OBJECT-TYPE
			SYNTAX	INTEGER
			MAX-ACCESS	read-only
			STATUS	current
			::= { hmWanMbus1E 15 }

hmWanMbus1EVIF05		OBJECT-TYPE
			SYNTAX	INTEGER
			MAX-ACCESS	read-only
			STATUS	current
			::= { hmWanMbus1E 16 }

hmWanMbus1EValue05		OBJECT-TYPE
			SYNTAX	INTEGER
			MAX-ACCESS	read-only
			STATUS	current
			::= { hmWanMbus1E 17 }

hmWanMbus1EVIF06		OBJECT-TYPE
			SYNTAX	INTEGER
			MAX-ACCESS	read-only
			STATUS	current
			::= { hmWanMbus1E 18 }

hmWanMbus1EValue06		OBJECT-TYPE
			SYNTAX	INTEGER
			MAX-ACCESS	read-only
			STATUS	current
			::= { hmWanMbus1E 19 }

hmWanMbus1EVIF07		OBJECT-TYPE
			SYNTAX	INTEGER
			MAX-ACCESS	read-only
			STATUS	current
			::= { hmWanMbus1E 20 }

hmWanMbus1EValue07		OBJECT-TYPE
			SYNTAX	INTEGER
			MAX-ACCESS	read-only
			STATUS	current
			::= { hmWanMbus1E 21 }

hmWanMbus1EVIF08		OBJECT-TYPE
			SYNTAX	INTEGER
			MAX-ACCESS	read-only
			STATUS	current
			::= { hmWanMbus1E 22 }

hmWanMbus1EValue08		OBJECT-TYPE
			SYNTAX	INTEGER
			MAX-ACCESS	read-only
			STATUS	current
			::= { hmWanMbus1E 23 }

hmWanMbus1EVIF09		OBJECT-TYPE
			SYNTAX	INTEGER
			MAX-ACCESS	read-only
			STATUS	current
			::= { hmWanMbus1E 24 }

hmWanMbus1EValue09		OBJECT-TYPE
			SYNTAX	INTEGER
			MAX-ACCESS	read-only
			STATUS	current
			::= { hmWanMbus1E 25 }

hmWanMbus1EVIF0A		OBJECT-TYPE
			SYNTAX	INTEGER
			MAX-ACCESS	read-only
			STATUS	current
			::= { hmWanMbus1E 26 }

hmWanMbus1EValue0A		OBJECT-TYPE
			SYNTAX	INTEGER
			MAX-ACCESS	read-only
			STATUS	current
			::= { hmWanMbus1E 27 }

hmWanMbus1EVIF0B		OBJECT-TYPE
			SYNTAX	INTEGER
			MAX-ACCESS	read-only
			STATUS	current
			::= { hmWanMbus1E 28 }

hmWanMbus1EValue0B		OBJECT-TYPE
			SYNTAX	INTEGER
			MAX-ACCESS	read-only
			STATUS	current
			::= { hmWanMbus1E 29 }

hmWanMbus1EVIF0C		OBJECT-TYPE
			SYNTAX	INTEGER
			MAX-ACCESS	read-only
			STATUS	current
			::= { hmWanMbus1E 30 }

hmWanMbus1EValue0C		OBJECT-TYPE
			SYNTAX	INTEGER
			MAX-ACCESS	read-only
			STATUS	current
			::= { hmWanMbus1E 31 }

hmWanMbus1EVIF0D		OBJECT-TYPE
			SYNTAX	INTEGER
			MAX-ACCESS	read-only
			STATUS	current
			::= { hmWanMbus1E 32 }

hmWanMbus1EValue0D		OBJECT-TYPE
			SYNTAX	INTEGER
			MAX-ACCESS	read-only
			STATUS	current
			::= { hmWanMbus1E 33 }

hmWanMbus1EVIF0E		OBJECT-TYPE
			SYNTAX	INTEGER
			MAX-ACCESS	read-only
			STATUS	current
			::= { hmWanMbus1E 34 }

hmWanMbus1EValue0E		OBJECT-TYPE
			SYNTAX	INTEGER
			MAX-ACCESS	read-only
			STATUS	current
			::= { hmWanMbus1E 35 }

hmWanMbus1EVIF0F		OBJECT-TYPE
			SYNTAX	INTEGER
			MAX-ACCESS	read-only
			STATUS	current
			::= { hmWanMbus1E 36 }

hmWanMbus1EValue0F		OBJECT-TYPE
			SYNTAX	INTEGER
			MAX-ACCESS	read-only
			STATUS	current
			::= { hmWanMbus1E 37 }

hmWanMbus1EVIF10		OBJECT-TYPE
			SYNTAX	INTEGER
			MAX-ACCESS	read-only
			STATUS	current
			::= { hmWanMbus1E 38 }

hmWanMbus1EValue10		OBJECT-TYPE
			SYNTAX	INTEGER
			MAX-ACCESS	read-only
			STATUS	current
			::= { hmWanMbus1E 39 }

hmWanMbus1EVIF11		OBJECT-TYPE
			SYNTAX	INTEGER
			MAX-ACCESS	read-only
			STATUS	current
			::= { hmWanMbus1E 40 }

hmWanMbus1EValue11		OBJECT-TYPE
			SYNTAX	INTEGER
			MAX-ACCESS	read-only
			STATUS	current
			::= { hmWanMbus1E 41 }

hmWanMbus1EVIF12		OBJECT-TYPE
			SYNTAX	INTEGER
			MAX-ACCESS	read-only
			STATUS	current
			::= { hmWanMbus1E 42 }

hmWanMbus1EValue12		OBJECT-TYPE
			SYNTAX	INTEGER
			MAX-ACCESS	read-only
			STATUS	current
			::= { hmWanMbus1E 43 }

hmWanMbus1EVIF13		OBJECT-TYPE
			SYNTAX	INTEGER
			MAX-ACCESS	read-only
			STATUS	current
			::= { hmWanMbus1E 44 }

hmWanMbus1EValue13		OBJECT-TYPE
			SYNTAX	INTEGER
			MAX-ACCESS	read-only
			STATUS	current
			::= { hmWanMbus1E 45 }

hmWanMbus1EVIF14		OBJECT-TYPE
			SYNTAX	INTEGER
			MAX-ACCESS	read-only
			STATUS	current
			::= { hmWanMbus1E 46 }

hmWanMbus1EValue14		OBJECT-TYPE
			SYNTAX	INTEGER
			MAX-ACCESS	read-only
			STATUS	current
			::= { hmWanMbus1E 47 }

hmWanMbus1EVIF15		OBJECT-TYPE
			SYNTAX	INTEGER
			MAX-ACCESS	read-only
			STATUS	current
			::= { hmWanMbus1E 48 }

hmWanMbus1EValue15		OBJECT-TYPE
			SYNTAX	INTEGER
			MAX-ACCESS	read-only
			STATUS	current
			::= { hmWanMbus1E 49 }

hmWanMbus1EVIF16		OBJECT-TYPE
			SYNTAX	INTEGER
			MAX-ACCESS	read-only
			STATUS	current
			::= { hmWanMbus1E 50 }

hmWanMbus1EValue16		OBJECT-TYPE
			SYNTAX	INTEGER
			MAX-ACCESS	read-only
			STATUS	current
			::= { hmWanMbus1E 51 }

hmWanMbus1EVIF17		OBJECT-TYPE
			SYNTAX	INTEGER
			MAX-ACCESS	read-only
			STATUS	current
			::= { hmWanMbus1E 52 }

hmWanMbus1EValue17		OBJECT-TYPE
			SYNTAX	INTEGER
			MAX-ACCESS	read-only
			STATUS	current
			::= { hmWanMbus1E 53 }

hmWanMbus1EVIF18		OBJECT-TYPE
			SYNTAX	INTEGER
			MAX-ACCESS	read-only
			STATUS	current
			::= { hmWanMbus1E 54 }

hmWanMbus1EValue18		OBJECT-TYPE
			SYNTAX	INTEGER
			MAX-ACCESS	read-only
			STATUS	current
			::= { hmWanMbus1E 55 }

hmWanMbus1EVIF19		OBJECT-TYPE
			SYNTAX	INTEGER
			MAX-ACCESS	read-only
			STATUS	current
			::= { hmWanMbus1E 56 }

hmWanMbus1EValue19		OBJECT-TYPE
			SYNTAX	INTEGER
			MAX-ACCESS	read-only
			STATUS	current
			::= { hmWanMbus1E 57 }

hmWanMbus1EVIF1A		OBJECT-TYPE
			SYNTAX	INTEGER
			MAX-ACCESS	read-only
			STATUS	current
			::= { hmWanMbus1E 58 }

hmWanMbus1EValue1A		OBJECT-TYPE
			SYNTAX	INTEGER
			MAX-ACCESS	read-only
			STATUS	current
			::= { hmWanMbus1E 59 }

hmWanMbus1EVIF1B		OBJECT-TYPE
			SYNTAX	INTEGER
			MAX-ACCESS	read-only
			STATUS	current
			::= { hmWanMbus1E 60 }

hmWanMbus1EValue1B		OBJECT-TYPE
			SYNTAX	INTEGER
			MAX-ACCESS	read-only
			STATUS	current
			::= { hmWanMbus1E 61 }

hmWanMbus1EVIF1C		OBJECT-TYPE
			SYNTAX	INTEGER
			MAX-ACCESS	read-only
			STATUS	current
			::= { hmWanMbus1E 62 }

hmWanMbus1EValue1C		OBJECT-TYPE
			SYNTAX	INTEGER
			MAX-ACCESS	read-only
			STATUS	current
			::= { hmWanMbus1E 63 }

hmWanMbus1EVIF1D		OBJECT-TYPE
			SYNTAX	INTEGER
			MAX-ACCESS	read-only
			STATUS	current
			::= { hmWanMbus1E 64 }

hmWanMbus1EValue1D		OBJECT-TYPE
			SYNTAX	INTEGER
			MAX-ACCESS	read-only
			STATUS	current
			::= { hmWanMbus1E 65 }

hmWanMbus1EVIF1E		OBJECT-TYPE
			SYNTAX	INTEGER
			MAX-ACCESS	read-only
			STATUS	current
			::= { hmWanMbus1E 66 }

hmWanMbus1EValue1E		OBJECT-TYPE
			SYNTAX	INTEGER
			MAX-ACCESS	read-only
			STATUS	current
			::= { hmWanMbus1E 67 }

hmWanMbus1EVIF1F		OBJECT-TYPE
			SYNTAX	INTEGER
			MAX-ACCESS	read-only
			STATUS	current
			::= { hmWanMbus1E 68 }

hmWanMbus1EValue1F		OBJECT-TYPE
			SYNTAX	INTEGER
			MAX-ACCESS	read-only
			STATUS	current
			::= { hmWanMbus1E 69 }

hmWanMbus1EVIF20		OBJECT-TYPE
			SYNTAX	INTEGER
			MAX-ACCESS	read-only
			STATUS	current
			::= { hmWanMbus1E 70 }

hmWanMbus1EValue20		OBJECT-TYPE
			SYNTAX	INTEGER
			MAX-ACCESS	read-only
			STATUS	current
			::= { hmWanMbus1E 71 }

hmWanMbus1EVIF21		OBJECT-TYPE
			SYNTAX	INTEGER
			MAX-ACCESS	read-only
			STATUS	current
			::= { hmWanMbus1E 72 }

hmWanMbus1EValue21		OBJECT-TYPE
			SYNTAX	INTEGER
			MAX-ACCESS	read-only
			STATUS	current
			::= { hmWanMbus1E 73 }

hmWanMbus1EVIF22		OBJECT-TYPE
			SYNTAX	INTEGER
			MAX-ACCESS	read-only
			STATUS	current
			::= { hmWanMbus1E 74 }

hmWanMbus1EValue22		OBJECT-TYPE
			SYNTAX	INTEGER
			MAX-ACCESS	read-only
			STATUS	current
			::= { hmWanMbus1E 75 }

hmWanMbus1EVIF23		OBJECT-TYPE
			SYNTAX	INTEGER
			MAX-ACCESS	read-only
			STATUS	current
			::= { hmWanMbus1E 76 }

hmWanMbus1EValue23		OBJECT-TYPE
			SYNTAX	INTEGER
			MAX-ACCESS	read-only
			STATUS	current
			::= { hmWanMbus1E 77 }

hmWanMbus1EVIF24		OBJECT-TYPE
			SYNTAX	INTEGER
			MAX-ACCESS	read-only
			STATUS	current
			::= { hmWanMbus1E 78 }

hmWanMbus1EValue24		OBJECT-TYPE
			SYNTAX	INTEGER
			MAX-ACCESS	read-only
			STATUS	current
			::= { hmWanMbus1E 79 }

hmWanMbus1EVIF25		OBJECT-TYPE
			SYNTAX	INTEGER
			MAX-ACCESS	read-only
			STATUS	current
			::= { hmWanMbus1E 80 }

hmWanMbus1EValue25		OBJECT-TYPE
			SYNTAX	INTEGER
			MAX-ACCESS	read-only
			STATUS	current
			::= { hmWanMbus1E 81 }

hmWanMbus1EVIF26		OBJECT-TYPE
			SYNTAX	INTEGER
			MAX-ACCESS	read-only
			STATUS	current
			::= { hmWanMbus1E 82 }

hmWanMbus1EValue26		OBJECT-TYPE
			SYNTAX	INTEGER
			MAX-ACCESS	read-only
			STATUS	current
			::= { hmWanMbus1E 83 }

hmWanMbus1EVIF27		OBJECT-TYPE
			SYNTAX	INTEGER
			MAX-ACCESS	read-only
			STATUS	current
			::= { hmWanMbus1E 84 }

hmWanMbus1EValue27		OBJECT-TYPE
			SYNTAX	INTEGER
			MAX-ACCESS	read-only
			STATUS	current
			::= { hmWanMbus1E 85 }

hmWanMbus1EVIF28		OBJECT-TYPE
			SYNTAX	INTEGER
			MAX-ACCESS	read-only
			STATUS	current
			::= { hmWanMbus1E 86 }

hmWanMbus1EValue28		OBJECT-TYPE
			SYNTAX	INTEGER
			MAX-ACCESS	read-only
			STATUS	current
			::= { hmWanMbus1E 87 }

hmWanMbus1EVIF29		OBJECT-TYPE
			SYNTAX	INTEGER
			MAX-ACCESS	read-only
			STATUS	current
			::= { hmWanMbus1E 88 }

hmWanMbus1EValue29		OBJECT-TYPE
			SYNTAX	INTEGER
			MAX-ACCESS	read-only
			STATUS	current
			::= { hmWanMbus1E 89 }

hmWanMbus1EVIF2A		OBJECT-TYPE
			SYNTAX	INTEGER
			MAX-ACCESS	read-only
			STATUS	current
			::= { hmWanMbus1E 90 }

hmWanMbus1EValue2A		OBJECT-TYPE
			SYNTAX	INTEGER
			MAX-ACCESS	read-only
			STATUS	current
			::= { hmWanMbus1E 91 }

hmWanMbus1EVIF2B		OBJECT-TYPE
			SYNTAX	INTEGER
			MAX-ACCESS	read-only
			STATUS	current
			::= { hmWanMbus1E 92 }

hmWanMbus1EValue2B		OBJECT-TYPE
			SYNTAX	INTEGER
			MAX-ACCESS	read-only
			STATUS	current
			::= { hmWanMbus1E 93 }

hmWanMbus1EVIF2C		OBJECT-TYPE
			SYNTAX	INTEGER
			MAX-ACCESS	read-only
			STATUS	current
			::= { hmWanMbus1E 94 }

hmWanMbus1EValue2C		OBJECT-TYPE
			SYNTAX	INTEGER
			MAX-ACCESS	read-only
			STATUS	current
			::= { hmWanMbus1E 95 }

hmWanMbus1EVIF2D		OBJECT-TYPE
			SYNTAX	INTEGER
			MAX-ACCESS	read-only
			STATUS	current
			::= { hmWanMbus1E 96 }

hmWanMbus1EValue2D		OBJECT-TYPE
			SYNTAX	INTEGER
			MAX-ACCESS	read-only
			STATUS	current
			::= { hmWanMbus1E 97 }

hmWanMbus1EVIF2E		OBJECT-TYPE
			SYNTAX	INTEGER
			MAX-ACCESS	read-only
			STATUS	current
			::= { hmWanMbus1E 98 }

hmWanMbus1EValue2E		OBJECT-TYPE
			SYNTAX	INTEGER
			MAX-ACCESS	read-only
			STATUS	current
			::= { hmWanMbus1E 99 }

hmWanMbus1EVIF2F		OBJECT-TYPE
			SYNTAX	INTEGER
			MAX-ACCESS	read-only
			STATUS	current
			::= { hmWanMbus1E 100 }

hmWanMbus1EValue2F		OBJECT-TYPE
			SYNTAX	INTEGER
			MAX-ACCESS	read-only
			STATUS	current
			::= { hmWanMbus1E 101 }

hmWanMbus1F			OBJECT IDENTIFIER ::= { hmWanMbus 31 }

hmWanMbus1FIdNumber		OBJECT-TYPE
			SYNTAX	Gauge32
			MAX-ACCESS	read-only
			STATUS	current
			::= { hmWanMbus1F 1 }

hmWanMbus1FManufacturer	OBJECT-TYPE
			SYNTAX	Gauge32
			MAX-ACCESS	read-only
			STATUS	current
			::= { hmWanMbus1F 2 }

hmWanMbus1FVersion		OBJECT-TYPE
			SYNTAX	Gauge32
			MAX-ACCESS	read-only
			STATUS	current
			::= { hmWanMbus1F 3 }

hmWanMbus1FMedium		OBJECT-TYPE
			SYNTAX	Gauge32
			MAX-ACCESS	read-only
			STATUS	current
			::= { hmWanMbus1F 4 }

hmWanMbus1FStatus		OBJECT-TYPE
			SYNTAX	Gauge32
			MAX-ACCESS	read-only
			STATUS	current
			::= { hmWanMbus1F 5 }

hmWanMbus1FVIF00		OBJECT-TYPE
			SYNTAX	INTEGER
			MAX-ACCESS	read-only
			STATUS	current
			::= { hmWanMbus1F 6 }

hmWanMbus1FValue00		OBJECT-TYPE
			SYNTAX	INTEGER
			MAX-ACCESS	read-only
			STATUS	current
			::= { hmWanMbus1F 7 }

hmWanMbus1FVIF01		OBJECT-TYPE
			SYNTAX	INTEGER
			MAX-ACCESS	read-only
			STATUS	current
			::= { hmWanMbus1F 8 }

hmWanMbus1FValue01		OBJECT-TYPE
			SYNTAX	INTEGER
			MAX-ACCESS	read-only
			STATUS	current
			::= { hmWanMbus1F 9 }

hmWanMbus1FVIF02		OBJECT-TYPE
			SYNTAX	INTEGER
			MAX-ACCESS	read-only
			STATUS	current
			::= { hmWanMbus1F 10 }

hmWanMbus1FValue02		OBJECT-TYPE
			SYNTAX	INTEGER
			MAX-ACCESS	read-only
			STATUS	current
			::= { hmWanMbus1F 11 }

hmWanMbus1FVIF03		OBJECT-TYPE
			SYNTAX	INTEGER
			MAX-ACCESS	read-only
			STATUS	current
			::= { hmWanMbus1F 12 }

hmWanMbus1FValue03		OBJECT-TYPE
			SYNTAX	INTEGER
			MAX-ACCESS	read-only
			STATUS	current
			::= { hmWanMbus1F 13 }

hmWanMbus1FVIF04		OBJECT-TYPE
			SYNTAX	INTEGER
			MAX-ACCESS	read-only
			STATUS	current
			::= { hmWanMbus1F 14 }

hmWanMbus1FValue04		OBJECT-TYPE
			SYNTAX	INTEGER
			MAX-ACCESS	read-only
			STATUS	current
			::= { hmWanMbus1F 15 }

hmWanMbus1FVIF05		OBJECT-TYPE
			SYNTAX	INTEGER
			MAX-ACCESS	read-only
			STATUS	current
			::= { hmWanMbus1F 16 }

hmWanMbus1FValue05		OBJECT-TYPE
			SYNTAX	INTEGER
			MAX-ACCESS	read-only
			STATUS	current
			::= { hmWanMbus1F 17 }

hmWanMbus1FVIF06		OBJECT-TYPE
			SYNTAX	INTEGER
			MAX-ACCESS	read-only
			STATUS	current
			::= { hmWanMbus1F 18 }

hmWanMbus1FValue06		OBJECT-TYPE
			SYNTAX	INTEGER
			MAX-ACCESS	read-only
			STATUS	current
			::= { hmWanMbus1F 19 }

hmWanMbus1FVIF07		OBJECT-TYPE
			SYNTAX	INTEGER
			MAX-ACCESS	read-only
			STATUS	current
			::= { hmWanMbus1F 20 }

hmWanMbus1FValue07		OBJECT-TYPE
			SYNTAX	INTEGER
			MAX-ACCESS	read-only
			STATUS	current
			::= { hmWanMbus1F 21 }

hmWanMbus1FVIF08		OBJECT-TYPE
			SYNTAX	INTEGER
			MAX-ACCESS	read-only
			STATUS	current
			::= { hmWanMbus1F 22 }

hmWanMbus1FValue08		OBJECT-TYPE
			SYNTAX	INTEGER
			MAX-ACCESS	read-only
			STATUS	current
			::= { hmWanMbus1F 23 }

hmWanMbus1FVIF09		OBJECT-TYPE
			SYNTAX	INTEGER
			MAX-ACCESS	read-only
			STATUS	current
			::= { hmWanMbus1F 24 }

hmWanMbus1FValue09		OBJECT-TYPE
			SYNTAX	INTEGER
			MAX-ACCESS	read-only
			STATUS	current
			::= { hmWanMbus1F 25 }

hmWanMbus1FVIF0A		OBJECT-TYPE
			SYNTAX	INTEGER
			MAX-ACCESS	read-only
			STATUS	current
			::= { hmWanMbus1F 26 }

hmWanMbus1FValue0A		OBJECT-TYPE
			SYNTAX	INTEGER
			MAX-ACCESS	read-only
			STATUS	current
			::= { hmWanMbus1F 27 }

hmWanMbus1FVIF0B		OBJECT-TYPE
			SYNTAX	INTEGER
			MAX-ACCESS	read-only
			STATUS	current
			::= { hmWanMbus1F 28 }

hmWanMbus1FValue0B		OBJECT-TYPE
			SYNTAX	INTEGER
			MAX-ACCESS	read-only
			STATUS	current
			::= { hmWanMbus1F 29 }

hmWanMbus1FVIF0C		OBJECT-TYPE
			SYNTAX	INTEGER
			MAX-ACCESS	read-only
			STATUS	current
			::= { hmWanMbus1F 30 }

hmWanMbus1FValue0C		OBJECT-TYPE
			SYNTAX	INTEGER
			MAX-ACCESS	read-only
			STATUS	current
			::= { hmWanMbus1F 31 }

hmWanMbus1FVIF0D		OBJECT-TYPE
			SYNTAX	INTEGER
			MAX-ACCESS	read-only
			STATUS	current
			::= { hmWanMbus1F 32 }

hmWanMbus1FValue0D		OBJECT-TYPE
			SYNTAX	INTEGER
			MAX-ACCESS	read-only
			STATUS	current
			::= { hmWanMbus1F 33 }

hmWanMbus1FVIF0E		OBJECT-TYPE
			SYNTAX	INTEGER
			MAX-ACCESS	read-only
			STATUS	current
			::= { hmWanMbus1F 34 }

hmWanMbus1FValue0E		OBJECT-TYPE
			SYNTAX	INTEGER
			MAX-ACCESS	read-only
			STATUS	current
			::= { hmWanMbus1F 35 }

hmWanMbus1FVIF0F		OBJECT-TYPE
			SYNTAX	INTEGER
			MAX-ACCESS	read-only
			STATUS	current
			::= { hmWanMbus1F 36 }

hmWanMbus1FValue0F		OBJECT-TYPE
			SYNTAX	INTEGER
			MAX-ACCESS	read-only
			STATUS	current
			::= { hmWanMbus1F 37 }

hmWanMbus1FVIF10		OBJECT-TYPE
			SYNTAX	INTEGER
			MAX-ACCESS	read-only
			STATUS	current
			::= { hmWanMbus1F 38 }

hmWanMbus1FValue10		OBJECT-TYPE
			SYNTAX	INTEGER
			MAX-ACCESS	read-only
			STATUS	current
			::= { hmWanMbus1F 39 }

hmWanMbus1FVIF11		OBJECT-TYPE
			SYNTAX	INTEGER
			MAX-ACCESS	read-only
			STATUS	current
			::= { hmWanMbus1F 40 }

hmWanMbus1FValue11		OBJECT-TYPE
			SYNTAX	INTEGER
			MAX-ACCESS	read-only
			STATUS	current
			::= { hmWanMbus1F 41 }

hmWanMbus1FVIF12		OBJECT-TYPE
			SYNTAX	INTEGER
			MAX-ACCESS	read-only
			STATUS	current
			::= { hmWanMbus1F 42 }

hmWanMbus1FValue12		OBJECT-TYPE
			SYNTAX	INTEGER
			MAX-ACCESS	read-only
			STATUS	current
			::= { hmWanMbus1F 43 }

hmWanMbus1FVIF13		OBJECT-TYPE
			SYNTAX	INTEGER
			MAX-ACCESS	read-only
			STATUS	current
			::= { hmWanMbus1F 44 }

hmWanMbus1FValue13		OBJECT-TYPE
			SYNTAX	INTEGER
			MAX-ACCESS	read-only
			STATUS	current
			::= { hmWanMbus1F 45 }

hmWanMbus1FVIF14		OBJECT-TYPE
			SYNTAX	INTEGER
			MAX-ACCESS	read-only
			STATUS	current
			::= { hmWanMbus1F 46 }

hmWanMbus1FValue14		OBJECT-TYPE
			SYNTAX	INTEGER
			MAX-ACCESS	read-only
			STATUS	current
			::= { hmWanMbus1F 47 }

hmWanMbus1FVIF15		OBJECT-TYPE
			SYNTAX	INTEGER
			MAX-ACCESS	read-only
			STATUS	current
			::= { hmWanMbus1F 48 }

hmWanMbus1FValue15		OBJECT-TYPE
			SYNTAX	INTEGER
			MAX-ACCESS	read-only
			STATUS	current
			::= { hmWanMbus1F 49 }

hmWanMbus1FVIF16		OBJECT-TYPE
			SYNTAX	INTEGER
			MAX-ACCESS	read-only
			STATUS	current
			::= { hmWanMbus1F 50 }

hmWanMbus1FValue16		OBJECT-TYPE
			SYNTAX	INTEGER
			MAX-ACCESS	read-only
			STATUS	current
			::= { hmWanMbus1F 51 }

hmWanMbus1FVIF17		OBJECT-TYPE
			SYNTAX	INTEGER
			MAX-ACCESS	read-only
			STATUS	current
			::= { hmWanMbus1F 52 }

hmWanMbus1FValue17		OBJECT-TYPE
			SYNTAX	INTEGER
			MAX-ACCESS	read-only
			STATUS	current
			::= { hmWanMbus1F 53 }

hmWanMbus1FVIF18		OBJECT-TYPE
			SYNTAX	INTEGER
			MAX-ACCESS	read-only
			STATUS	current
			::= { hmWanMbus1F 54 }

hmWanMbus1FValue18		OBJECT-TYPE
			SYNTAX	INTEGER
			MAX-ACCESS	read-only
			STATUS	current
			::= { hmWanMbus1F 55 }

hmWanMbus1FVIF19		OBJECT-TYPE
			SYNTAX	INTEGER
			MAX-ACCESS	read-only
			STATUS	current
			::= { hmWanMbus1F 56 }

hmWanMbus1FValue19		OBJECT-TYPE
			SYNTAX	INTEGER
			MAX-ACCESS	read-only
			STATUS	current
			::= { hmWanMbus1F 57 }

hmWanMbus1FVIF1A		OBJECT-TYPE
			SYNTAX	INTEGER
			MAX-ACCESS	read-only
			STATUS	current
			::= { hmWanMbus1F 58 }

hmWanMbus1FValue1A		OBJECT-TYPE
			SYNTAX	INTEGER
			MAX-ACCESS	read-only
			STATUS	current
			::= { hmWanMbus1F 59 }

hmWanMbus1FVIF1B		OBJECT-TYPE
			SYNTAX	INTEGER
			MAX-ACCESS	read-only
			STATUS	current
			::= { hmWanMbus1F 60 }

hmWanMbus1FValue1B		OBJECT-TYPE
			SYNTAX	INTEGER
			MAX-ACCESS	read-only
			STATUS	current
			::= { hmWanMbus1F 61 }

hmWanMbus1FVIF1C		OBJECT-TYPE
			SYNTAX	INTEGER
			MAX-ACCESS	read-only
			STATUS	current
			::= { hmWanMbus1F 62 }

hmWanMbus1FValue1C		OBJECT-TYPE
			SYNTAX	INTEGER
			MAX-ACCESS	read-only
			STATUS	current
			::= { hmWanMbus1F 63 }

hmWanMbus1FVIF1D		OBJECT-TYPE
			SYNTAX	INTEGER
			MAX-ACCESS	read-only
			STATUS	current
			::= { hmWanMbus1F 64 }

hmWanMbus1FValue1D		OBJECT-TYPE
			SYNTAX	INTEGER
			MAX-ACCESS	read-only
			STATUS	current
			::= { hmWanMbus1F 65 }

hmWanMbus1FVIF1E		OBJECT-TYPE
			SYNTAX	INTEGER
			MAX-ACCESS	read-only
			STATUS	current
			::= { hmWanMbus1F 66 }

hmWanMbus1FValue1E		OBJECT-TYPE
			SYNTAX	INTEGER
			MAX-ACCESS	read-only
			STATUS	current
			::= { hmWanMbus1F 67 }

hmWanMbus1FVIF1F		OBJECT-TYPE
			SYNTAX	INTEGER
			MAX-ACCESS	read-only
			STATUS	current
			::= { hmWanMbus1F 68 }

hmWanMbus1FValue1F		OBJECT-TYPE
			SYNTAX	INTEGER
			MAX-ACCESS	read-only
			STATUS	current
			::= { hmWanMbus1F 69 }

hmWanMbus1FVIF20		OBJECT-TYPE
			SYNTAX	INTEGER
			MAX-ACCESS	read-only
			STATUS	current
			::= { hmWanMbus1F 70 }

hmWanMbus1FValue20		OBJECT-TYPE
			SYNTAX	INTEGER
			MAX-ACCESS	read-only
			STATUS	current
			::= { hmWanMbus1F 71 }

hmWanMbus1FVIF21		OBJECT-TYPE
			SYNTAX	INTEGER
			MAX-ACCESS	read-only
			STATUS	current
			::= { hmWanMbus1F 72 }

hmWanMbus1FValue21		OBJECT-TYPE
			SYNTAX	INTEGER
			MAX-ACCESS	read-only
			STATUS	current
			::= { hmWanMbus1F 73 }

hmWanMbus1FVIF22		OBJECT-TYPE
			SYNTAX	INTEGER
			MAX-ACCESS	read-only
			STATUS	current
			::= { hmWanMbus1F 74 }

hmWanMbus1FValue22		OBJECT-TYPE
			SYNTAX	INTEGER
			MAX-ACCESS	read-only
			STATUS	current
			::= { hmWanMbus1F 75 }

hmWanMbus1FVIF23		OBJECT-TYPE
			SYNTAX	INTEGER
			MAX-ACCESS	read-only
			STATUS	current
			::= { hmWanMbus1F 76 }

hmWanMbus1FValue23		OBJECT-TYPE
			SYNTAX	INTEGER
			MAX-ACCESS	read-only
			STATUS	current
			::= { hmWanMbus1F 77 }

hmWanMbus1FVIF24		OBJECT-TYPE
			SYNTAX	INTEGER
			MAX-ACCESS	read-only
			STATUS	current
			::= { hmWanMbus1F 78 }

hmWanMbus1FValue24		OBJECT-TYPE
			SYNTAX	INTEGER
			MAX-ACCESS	read-only
			STATUS	current
			::= { hmWanMbus1F 79 }

hmWanMbus1FVIF25		OBJECT-TYPE
			SYNTAX	INTEGER
			MAX-ACCESS	read-only
			STATUS	current
			::= { hmWanMbus1F 80 }

hmWanMbus1FValue25		OBJECT-TYPE
			SYNTAX	INTEGER
			MAX-ACCESS	read-only
			STATUS	current
			::= { hmWanMbus1F 81 }

hmWanMbus1FVIF26		OBJECT-TYPE
			SYNTAX	INTEGER
			MAX-ACCESS	read-only
			STATUS	current
			::= { hmWanMbus1F 82 }

hmWanMbus1FValue26		OBJECT-TYPE
			SYNTAX	INTEGER
			MAX-ACCESS	read-only
			STATUS	current
			::= { hmWanMbus1F 83 }

hmWanMbus1FVIF27		OBJECT-TYPE
			SYNTAX	INTEGER
			MAX-ACCESS	read-only
			STATUS	current
			::= { hmWanMbus1F 84 }

hmWanMbus1FValue27		OBJECT-TYPE
			SYNTAX	INTEGER
			MAX-ACCESS	read-only
			STATUS	current
			::= { hmWanMbus1F 85 }

hmWanMbus1FVIF28		OBJECT-TYPE
			SYNTAX	INTEGER
			MAX-ACCESS	read-only
			STATUS	current
			::= { hmWanMbus1F 86 }

hmWanMbus1FValue28		OBJECT-TYPE
			SYNTAX	INTEGER
			MAX-ACCESS	read-only
			STATUS	current
			::= { hmWanMbus1F 87 }

hmWanMbus1FVIF29		OBJECT-TYPE
			SYNTAX	INTEGER
			MAX-ACCESS	read-only
			STATUS	current
			::= { hmWanMbus1F 88 }

hmWanMbus1FValue29		OBJECT-TYPE
			SYNTAX	INTEGER
			MAX-ACCESS	read-only
			STATUS	current
			::= { hmWanMbus1F 89 }

hmWanMbus1FVIF2A		OBJECT-TYPE
			SYNTAX	INTEGER
			MAX-ACCESS	read-only
			STATUS	current
			::= { hmWanMbus1F 90 }

hmWanMbus1FValue2A		OBJECT-TYPE
			SYNTAX	INTEGER
			MAX-ACCESS	read-only
			STATUS	current
			::= { hmWanMbus1F 91 }

hmWanMbus1FVIF2B		OBJECT-TYPE
			SYNTAX	INTEGER
			MAX-ACCESS	read-only
			STATUS	current
			::= { hmWanMbus1F 92 }

hmWanMbus1FValue2B		OBJECT-TYPE
			SYNTAX	INTEGER
			MAX-ACCESS	read-only
			STATUS	current
			::= { hmWanMbus1F 93 }

hmWanMbus1FVIF2C		OBJECT-TYPE
			SYNTAX	INTEGER
			MAX-ACCESS	read-only
			STATUS	current
			::= { hmWanMbus1F 94 }

hmWanMbus1FValue2C		OBJECT-TYPE
			SYNTAX	INTEGER
			MAX-ACCESS	read-only
			STATUS	current
			::= { hmWanMbus1F 95 }

hmWanMbus1FVIF2D		OBJECT-TYPE
			SYNTAX	INTEGER
			MAX-ACCESS	read-only
			STATUS	current
			::= { hmWanMbus1F 96 }

hmWanMbus1FValue2D		OBJECT-TYPE
			SYNTAX	INTEGER
			MAX-ACCESS	read-only
			STATUS	current
			::= { hmWanMbus1F 97 }

hmWanMbus1FVIF2E		OBJECT-TYPE
			SYNTAX	INTEGER
			MAX-ACCESS	read-only
			STATUS	current
			::= { hmWanMbus1F 98 }

hmWanMbus1FValue2E		OBJECT-TYPE
			SYNTAX	INTEGER
			MAX-ACCESS	read-only
			STATUS	current
			::= { hmWanMbus1F 99 }

hmWanMbus1FVIF2F		OBJECT-TYPE
			SYNTAX	INTEGER
			MAX-ACCESS	read-only
			STATUS	current
			::= { hmWanMbus1F 100 }

hmWanMbus1FValue2F		OBJECT-TYPE
			SYNTAX	INTEGER
			MAX-ACCESS	read-only
			STATUS	current
			::= { hmWanMbus1F 101 }

hmWanMbus20			OBJECT IDENTIFIER ::= { hmWanMbus 32 }

hmWanMbus20IdNumber		OBJECT-TYPE
			SYNTAX	Gauge32
			MAX-ACCESS	read-only
			STATUS	current
			::= { hmWanMbus20 1 }

hmWanMbus20Manufacturer	OBJECT-TYPE
			SYNTAX	Gauge32
			MAX-ACCESS	read-only
			STATUS	current
			::= { hmWanMbus20 2 }

hmWanMbus20Version		OBJECT-TYPE
			SYNTAX	Gauge32
			MAX-ACCESS	read-only
			STATUS	current
			::= { hmWanMbus20 3 }

hmWanMbus20Medium		OBJECT-TYPE
			SYNTAX	Gauge32
			MAX-ACCESS	read-only
			STATUS	current
			::= { hmWanMbus20 4 }

hmWanMbus20Status		OBJECT-TYPE
			SYNTAX	Gauge32
			MAX-ACCESS	read-only
			STATUS	current
			::= { hmWanMbus20 5 }

hmWanMbus20VIF00		OBJECT-TYPE
			SYNTAX	INTEGER
			MAX-ACCESS	read-only
			STATUS	current
			::= { hmWanMbus20 6 }

hmWanMbus20Value00		OBJECT-TYPE
			SYNTAX	INTEGER
			MAX-ACCESS	read-only
			STATUS	current
			::= { hmWanMbus20 7 }

hmWanMbus20VIF01		OBJECT-TYPE
			SYNTAX	INTEGER
			MAX-ACCESS	read-only
			STATUS	current
			::= { hmWanMbus20 8 }

hmWanMbus20Value01		OBJECT-TYPE
			SYNTAX	INTEGER
			MAX-ACCESS	read-only
			STATUS	current
			::= { hmWanMbus20 9 }

hmWanMbus20VIF02		OBJECT-TYPE
			SYNTAX	INTEGER
			MAX-ACCESS	read-only
			STATUS	current
			::= { hmWanMbus20 10 }

hmWanMbus20Value02		OBJECT-TYPE
			SYNTAX	INTEGER
			MAX-ACCESS	read-only
			STATUS	current
			::= { hmWanMbus20 11 }

hmWanMbus20VIF03		OBJECT-TYPE
			SYNTAX	INTEGER
			MAX-ACCESS	read-only
			STATUS	current
			::= { hmWanMbus20 12 }

hmWanMbus20Value03		OBJECT-TYPE
			SYNTAX	INTEGER
			MAX-ACCESS	read-only
			STATUS	current
			::= { hmWanMbus20 13 }

hmWanMbus20VIF04		OBJECT-TYPE
			SYNTAX	INTEGER
			MAX-ACCESS	read-only
			STATUS	current
			::= { hmWanMbus20 14 }

hmWanMbus20Value04		OBJECT-TYPE
			SYNTAX	INTEGER
			MAX-ACCESS	read-only
			STATUS	current
			::= { hmWanMbus20 15 }

hmWanMbus20VIF05		OBJECT-TYPE
			SYNTAX	INTEGER
			MAX-ACCESS	read-only
			STATUS	current
			::= { hmWanMbus20 16 }

hmWanMbus20Value05		OBJECT-TYPE
			SYNTAX	INTEGER
			MAX-ACCESS	read-only
			STATUS	current
			::= { hmWanMbus20 17 }

hmWanMbus20VIF06		OBJECT-TYPE
			SYNTAX	INTEGER
			MAX-ACCESS	read-only
			STATUS	current
			::= { hmWanMbus20 18 }

hmWanMbus20Value06		OBJECT-TYPE
			SYNTAX	INTEGER
			MAX-ACCESS	read-only
			STATUS	current
			::= { hmWanMbus20 19 }

hmWanMbus20VIF07		OBJECT-TYPE
			SYNTAX	INTEGER
			MAX-ACCESS	read-only
			STATUS	current
			::= { hmWanMbus20 20 }

hmWanMbus20Value07		OBJECT-TYPE
			SYNTAX	INTEGER
			MAX-ACCESS	read-only
			STATUS	current
			::= { hmWanMbus20 21 }

hmWanMbus20VIF08		OBJECT-TYPE
			SYNTAX	INTEGER
			MAX-ACCESS	read-only
			STATUS	current
			::= { hmWanMbus20 22 }

hmWanMbus20Value08		OBJECT-TYPE
			SYNTAX	INTEGER
			MAX-ACCESS	read-only
			STATUS	current
			::= { hmWanMbus20 23 }

hmWanMbus20VIF09		OBJECT-TYPE
			SYNTAX	INTEGER
			MAX-ACCESS	read-only
			STATUS	current
			::= { hmWanMbus20 24 }

hmWanMbus20Value09		OBJECT-TYPE
			SYNTAX	INTEGER
			MAX-ACCESS	read-only
			STATUS	current
			::= { hmWanMbus20 25 }

hmWanMbus20VIF0A		OBJECT-TYPE
			SYNTAX	INTEGER
			MAX-ACCESS	read-only
			STATUS	current
			::= { hmWanMbus20 26 }

hmWanMbus20Value0A		OBJECT-TYPE
			SYNTAX	INTEGER
			MAX-ACCESS	read-only
			STATUS	current
			::= { hmWanMbus20 27 }

hmWanMbus20VIF0B		OBJECT-TYPE
			SYNTAX	INTEGER
			MAX-ACCESS	read-only
			STATUS	current
			::= { hmWanMbus20 28 }

hmWanMbus20Value0B		OBJECT-TYPE
			SYNTAX	INTEGER
			MAX-ACCESS	read-only
			STATUS	current
			::= { hmWanMbus20 29 }

hmWanMbus20VIF0C		OBJECT-TYPE
			SYNTAX	INTEGER
			MAX-ACCESS	read-only
			STATUS	current
			::= { hmWanMbus20 30 }

hmWanMbus20Value0C		OBJECT-TYPE
			SYNTAX	INTEGER
			MAX-ACCESS	read-only
			STATUS	current
			::= { hmWanMbus20 31 }

hmWanMbus20VIF0D		OBJECT-TYPE
			SYNTAX	INTEGER
			MAX-ACCESS	read-only
			STATUS	current
			::= { hmWanMbus20 32 }

hmWanMbus20Value0D		OBJECT-TYPE
			SYNTAX	INTEGER
			MAX-ACCESS	read-only
			STATUS	current
			::= { hmWanMbus20 33 }

hmWanMbus20VIF0E		OBJECT-TYPE
			SYNTAX	INTEGER
			MAX-ACCESS	read-only
			STATUS	current
			::= { hmWanMbus20 34 }

hmWanMbus20Value0E		OBJECT-TYPE
			SYNTAX	INTEGER
			MAX-ACCESS	read-only
			STATUS	current
			::= { hmWanMbus20 35 }

hmWanMbus20VIF0F		OBJECT-TYPE
			SYNTAX	INTEGER
			MAX-ACCESS	read-only
			STATUS	current
			::= { hmWanMbus20 36 }

hmWanMbus20Value0F		OBJECT-TYPE
			SYNTAX	INTEGER
			MAX-ACCESS	read-only
			STATUS	current
			::= { hmWanMbus20 37 }

hmWanMbus20VIF10		OBJECT-TYPE
			SYNTAX	INTEGER
			MAX-ACCESS	read-only
			STATUS	current
			::= { hmWanMbus20 38 }

hmWanMbus20Value10		OBJECT-TYPE
			SYNTAX	INTEGER
			MAX-ACCESS	read-only
			STATUS	current
			::= { hmWanMbus20 39 }

hmWanMbus20VIF11		OBJECT-TYPE
			SYNTAX	INTEGER
			MAX-ACCESS	read-only
			STATUS	current
			::= { hmWanMbus20 40 }

hmWanMbus20Value11		OBJECT-TYPE
			SYNTAX	INTEGER
			MAX-ACCESS	read-only
			STATUS	current
			::= { hmWanMbus20 41 }

hmWanMbus20VIF12		OBJECT-TYPE
			SYNTAX	INTEGER
			MAX-ACCESS	read-only
			STATUS	current
			::= { hmWanMbus20 42 }

hmWanMbus20Value12		OBJECT-TYPE
			SYNTAX	INTEGER
			MAX-ACCESS	read-only
			STATUS	current
			::= { hmWanMbus20 43 }

hmWanMbus20VIF13		OBJECT-TYPE
			SYNTAX	INTEGER
			MAX-ACCESS	read-only
			STATUS	current
			::= { hmWanMbus20 44 }

hmWanMbus20Value13		OBJECT-TYPE
			SYNTAX	INTEGER
			MAX-ACCESS	read-only
			STATUS	current
			::= { hmWanMbus20 45 }

hmWanMbus20VIF14		OBJECT-TYPE
			SYNTAX	INTEGER
			MAX-ACCESS	read-only
			STATUS	current
			::= { hmWanMbus20 46 }

hmWanMbus20Value14		OBJECT-TYPE
			SYNTAX	INTEGER
			MAX-ACCESS	read-only
			STATUS	current
			::= { hmWanMbus20 47 }

hmWanMbus20VIF15		OBJECT-TYPE
			SYNTAX	INTEGER
			MAX-ACCESS	read-only
			STATUS	current
			::= { hmWanMbus20 48 }

hmWanMbus20Value15		OBJECT-TYPE
			SYNTAX	INTEGER
			MAX-ACCESS	read-only
			STATUS	current
			::= { hmWanMbus20 49 }

hmWanMbus20VIF16		OBJECT-TYPE
			SYNTAX	INTEGER
			MAX-ACCESS	read-only
			STATUS	current
			::= { hmWanMbus20 50 }

hmWanMbus20Value16		OBJECT-TYPE
			SYNTAX	INTEGER
			MAX-ACCESS	read-only
			STATUS	current
			::= { hmWanMbus20 51 }

hmWanMbus20VIF17		OBJECT-TYPE
			SYNTAX	INTEGER
			MAX-ACCESS	read-only
			STATUS	current
			::= { hmWanMbus20 52 }

hmWanMbus20Value17		OBJECT-TYPE
			SYNTAX	INTEGER
			MAX-ACCESS	read-only
			STATUS	current
			::= { hmWanMbus20 53 }

hmWanMbus20VIF18		OBJECT-TYPE
			SYNTAX	INTEGER
			MAX-ACCESS	read-only
			STATUS	current
			::= { hmWanMbus20 54 }

hmWanMbus20Value18		OBJECT-TYPE
			SYNTAX	INTEGER
			MAX-ACCESS	read-only
			STATUS	current
			::= { hmWanMbus20 55 }

hmWanMbus20VIF19		OBJECT-TYPE
			SYNTAX	INTEGER
			MAX-ACCESS	read-only
			STATUS	current
			::= { hmWanMbus20 56 }

hmWanMbus20Value19		OBJECT-TYPE
			SYNTAX	INTEGER
			MAX-ACCESS	read-only
			STATUS	current
			::= { hmWanMbus20 57 }

hmWanMbus20VIF1A		OBJECT-TYPE
			SYNTAX	INTEGER
			MAX-ACCESS	read-only
			STATUS	current
			::= { hmWanMbus20 58 }

hmWanMbus20Value1A		OBJECT-TYPE
			SYNTAX	INTEGER
			MAX-ACCESS	read-only
			STATUS	current
			::= { hmWanMbus20 59 }

hmWanMbus20VIF1B		OBJECT-TYPE
			SYNTAX	INTEGER
			MAX-ACCESS	read-only
			STATUS	current
			::= { hmWanMbus20 60 }

hmWanMbus20Value1B		OBJECT-TYPE
			SYNTAX	INTEGER
			MAX-ACCESS	read-only
			STATUS	current
			::= { hmWanMbus20 61 }

hmWanMbus20VIF1C		OBJECT-TYPE
			SYNTAX	INTEGER
			MAX-ACCESS	read-only
			STATUS	current
			::= { hmWanMbus20 62 }

hmWanMbus20Value1C		OBJECT-TYPE
			SYNTAX	INTEGER
			MAX-ACCESS	read-only
			STATUS	current
			::= { hmWanMbus20 63 }

hmWanMbus20VIF1D		OBJECT-TYPE
			SYNTAX	INTEGER
			MAX-ACCESS	read-only
			STATUS	current
			::= { hmWanMbus20 64 }

hmWanMbus20Value1D		OBJECT-TYPE
			SYNTAX	INTEGER
			MAX-ACCESS	read-only
			STATUS	current
			::= { hmWanMbus20 65 }

hmWanMbus20VIF1E		OBJECT-TYPE
			SYNTAX	INTEGER
			MAX-ACCESS	read-only
			STATUS	current
			::= { hmWanMbus20 66 }

hmWanMbus20Value1E		OBJECT-TYPE
			SYNTAX	INTEGER
			MAX-ACCESS	read-only
			STATUS	current
			::= { hmWanMbus20 67 }

hmWanMbus20VIF1F		OBJECT-TYPE
			SYNTAX	INTEGER
			MAX-ACCESS	read-only
			STATUS	current
			::= { hmWanMbus20 68 }

hmWanMbus20Value1F		OBJECT-TYPE
			SYNTAX	INTEGER
			MAX-ACCESS	read-only
			STATUS	current
			::= { hmWanMbus20 69 }

hmWanMbus20VIF20		OBJECT-TYPE
			SYNTAX	INTEGER
			MAX-ACCESS	read-only
			STATUS	current
			::= { hmWanMbus20 70 }

hmWanMbus20Value20		OBJECT-TYPE
			SYNTAX	INTEGER
			MAX-ACCESS	read-only
			STATUS	current
			::= { hmWanMbus20 71 }

hmWanMbus20VIF21		OBJECT-TYPE
			SYNTAX	INTEGER
			MAX-ACCESS	read-only
			STATUS	current
			::= { hmWanMbus20 72 }

hmWanMbus20Value21		OBJECT-TYPE
			SYNTAX	INTEGER
			MAX-ACCESS	read-only
			STATUS	current
			::= { hmWanMbus20 73 }

hmWanMbus20VIF22		OBJECT-TYPE
			SYNTAX	INTEGER
			MAX-ACCESS	read-only
			STATUS	current
			::= { hmWanMbus20 74 }

hmWanMbus20Value22		OBJECT-TYPE
			SYNTAX	INTEGER
			MAX-ACCESS	read-only
			STATUS	current
			::= { hmWanMbus20 75 }

hmWanMbus20VIF23		OBJECT-TYPE
			SYNTAX	INTEGER
			MAX-ACCESS	read-only
			STATUS	current
			::= { hmWanMbus20 76 }

hmWanMbus20Value23		OBJECT-TYPE
			SYNTAX	INTEGER
			MAX-ACCESS	read-only
			STATUS	current
			::= { hmWanMbus20 77 }

hmWanMbus20VIF24		OBJECT-TYPE
			SYNTAX	INTEGER
			MAX-ACCESS	read-only
			STATUS	current
			::= { hmWanMbus20 78 }

hmWanMbus20Value24		OBJECT-TYPE
			SYNTAX	INTEGER
			MAX-ACCESS	read-only
			STATUS	current
			::= { hmWanMbus20 79 }

hmWanMbus20VIF25		OBJECT-TYPE
			SYNTAX	INTEGER
			MAX-ACCESS	read-only
			STATUS	current
			::= { hmWanMbus20 80 }

hmWanMbus20Value25		OBJECT-TYPE
			SYNTAX	INTEGER
			MAX-ACCESS	read-only
			STATUS	current
			::= { hmWanMbus20 81 }

hmWanMbus20VIF26		OBJECT-TYPE
			SYNTAX	INTEGER
			MAX-ACCESS	read-only
			STATUS	current
			::= { hmWanMbus20 82 }

hmWanMbus20Value26		OBJECT-TYPE
			SYNTAX	INTEGER
			MAX-ACCESS	read-only
			STATUS	current
			::= { hmWanMbus20 83 }

hmWanMbus20VIF27		OBJECT-TYPE
			SYNTAX	INTEGER
			MAX-ACCESS	read-only
			STATUS	current
			::= { hmWanMbus20 84 }

hmWanMbus20Value27		OBJECT-TYPE
			SYNTAX	INTEGER
			MAX-ACCESS	read-only
			STATUS	current
			::= { hmWanMbus20 85 }

hmWanMbus20VIF28		OBJECT-TYPE
			SYNTAX	INTEGER
			MAX-ACCESS	read-only
			STATUS	current
			::= { hmWanMbus20 86 }

hmWanMbus20Value28		OBJECT-TYPE
			SYNTAX	INTEGER
			MAX-ACCESS	read-only
			STATUS	current
			::= { hmWanMbus20 87 }

hmWanMbus20VIF29		OBJECT-TYPE
			SYNTAX	INTEGER
			MAX-ACCESS	read-only
			STATUS	current
			::= { hmWanMbus20 88 }

hmWanMbus20Value29		OBJECT-TYPE
			SYNTAX	INTEGER
			MAX-ACCESS	read-only
			STATUS	current
			::= { hmWanMbus20 89 }

hmWanMbus20VIF2A		OBJECT-TYPE
			SYNTAX	INTEGER
			MAX-ACCESS	read-only
			STATUS	current
			::= { hmWanMbus20 90 }

hmWanMbus20Value2A		OBJECT-TYPE
			SYNTAX	INTEGER
			MAX-ACCESS	read-only
			STATUS	current
			::= { hmWanMbus20 91 }

hmWanMbus20VIF2B		OBJECT-TYPE
			SYNTAX	INTEGER
			MAX-ACCESS	read-only
			STATUS	current
			::= { hmWanMbus20 92 }

hmWanMbus20Value2B		OBJECT-TYPE
			SYNTAX	INTEGER
			MAX-ACCESS	read-only
			STATUS	current
			::= { hmWanMbus20 93 }

hmWanMbus20VIF2C		OBJECT-TYPE
			SYNTAX	INTEGER
			MAX-ACCESS	read-only
			STATUS	current
			::= { hmWanMbus20 94 }

hmWanMbus20Value2C		OBJECT-TYPE
			SYNTAX	INTEGER
			MAX-ACCESS	read-only
			STATUS	current
			::= { hmWanMbus20 95 }

hmWanMbus20VIF2D		OBJECT-TYPE
			SYNTAX	INTEGER
			MAX-ACCESS	read-only
			STATUS	current
			::= { hmWanMbus20 96 }

hmWanMbus20Value2D		OBJECT-TYPE
			SYNTAX	INTEGER
			MAX-ACCESS	read-only
			STATUS	current
			::= { hmWanMbus20 97 }

hmWanMbus20VIF2E		OBJECT-TYPE
			SYNTAX	INTEGER
			MAX-ACCESS	read-only
			STATUS	current
			::= { hmWanMbus20 98 }

hmWanMbus20Value2E		OBJECT-TYPE
			SYNTAX	INTEGER
			MAX-ACCESS	read-only
			STATUS	current
			::= { hmWanMbus20 99 }

hmWanMbus20VIF2F		OBJECT-TYPE
			SYNTAX	INTEGER
			MAX-ACCESS	read-only
			STATUS	current
			::= { hmWanMbus20 100 }

hmWanMbus20Value2F		OBJECT-TYPE
			SYNTAX	INTEGER
			MAX-ACCESS	read-only
			STATUS	current
			::= { hmWanMbus20 101 }

hmWanMbus21			OBJECT IDENTIFIER ::= { hmWanMbus 33 }

hmWanMbus21IdNumber		OBJECT-TYPE
			SYNTAX	Gauge32
			MAX-ACCESS	read-only
			STATUS	current
			::= { hmWanMbus21 1 }

hmWanMbus21Manufacturer	OBJECT-TYPE
			SYNTAX	Gauge32
			MAX-ACCESS	read-only
			STATUS	current
			::= { hmWanMbus21 2 }

hmWanMbus21Version		OBJECT-TYPE
			SYNTAX	Gauge32
			MAX-ACCESS	read-only
			STATUS	current
			::= { hmWanMbus21 3 }

hmWanMbus21Medium		OBJECT-TYPE
			SYNTAX	Gauge32
			MAX-ACCESS	read-only
			STATUS	current
			::= { hmWanMbus21 4 }

hmWanMbus21Status		OBJECT-TYPE
			SYNTAX	Gauge32
			MAX-ACCESS	read-only
			STATUS	current
			::= { hmWanMbus21 5 }

hmWanMbus21VIF00		OBJECT-TYPE
			SYNTAX	INTEGER
			MAX-ACCESS	read-only
			STATUS	current
			::= { hmWanMbus21 6 }

hmWanMbus21Value00		OBJECT-TYPE
			SYNTAX	INTEGER
			MAX-ACCESS	read-only
			STATUS	current
			::= { hmWanMbus21 7 }

hmWanMbus21VIF01		OBJECT-TYPE
			SYNTAX	INTEGER
			MAX-ACCESS	read-only
			STATUS	current
			::= { hmWanMbus21 8 }

hmWanMbus21Value01		OBJECT-TYPE
			SYNTAX	INTEGER
			MAX-ACCESS	read-only
			STATUS	current
			::= { hmWanMbus21 9 }

hmWanMbus21VIF02		OBJECT-TYPE
			SYNTAX	INTEGER
			MAX-ACCESS	read-only
			STATUS	current
			::= { hmWanMbus21 10 }

hmWanMbus21Value02		OBJECT-TYPE
			SYNTAX	INTEGER
			MAX-ACCESS	read-only
			STATUS	current
			::= { hmWanMbus21 11 }

hmWanMbus21VIF03		OBJECT-TYPE
			SYNTAX	INTEGER
			MAX-ACCESS	read-only
			STATUS	current
			::= { hmWanMbus21 12 }

hmWanMbus21Value03		OBJECT-TYPE
			SYNTAX	INTEGER
			MAX-ACCESS	read-only
			STATUS	current
			::= { hmWanMbus21 13 }

hmWanMbus21VIF04		OBJECT-TYPE
			SYNTAX	INTEGER
			MAX-ACCESS	read-only
			STATUS	current
			::= { hmWanMbus21 14 }

hmWanMbus21Value04		OBJECT-TYPE
			SYNTAX	INTEGER
			MAX-ACCESS	read-only
			STATUS	current
			::= { hmWanMbus21 15 }

hmWanMbus21VIF05		OBJECT-TYPE
			SYNTAX	INTEGER
			MAX-ACCESS	read-only
			STATUS	current
			::= { hmWanMbus21 16 }

hmWanMbus21Value05		OBJECT-TYPE
			SYNTAX	INTEGER
			MAX-ACCESS	read-only
			STATUS	current
			::= { hmWanMbus21 17 }

hmWanMbus21VIF06		OBJECT-TYPE
			SYNTAX	INTEGER
			MAX-ACCESS	read-only
			STATUS	current
			::= { hmWanMbus21 18 }

hmWanMbus21Value06		OBJECT-TYPE
			SYNTAX	INTEGER
			MAX-ACCESS	read-only
			STATUS	current
			::= { hmWanMbus21 19 }

hmWanMbus21VIF07		OBJECT-TYPE
			SYNTAX	INTEGER
			MAX-ACCESS	read-only
			STATUS	current
			::= { hmWanMbus21 20 }

hmWanMbus21Value07		OBJECT-TYPE
			SYNTAX	INTEGER
			MAX-ACCESS	read-only
			STATUS	current
			::= { hmWanMbus21 21 }

hmWanMbus21VIF08		OBJECT-TYPE
			SYNTAX	INTEGER
			MAX-ACCESS	read-only
			STATUS	current
			::= { hmWanMbus21 22 }

hmWanMbus21Value08		OBJECT-TYPE
			SYNTAX	INTEGER
			MAX-ACCESS	read-only
			STATUS	current
			::= { hmWanMbus21 23 }

hmWanMbus21VIF09		OBJECT-TYPE
			SYNTAX	INTEGER
			MAX-ACCESS	read-only
			STATUS	current
			::= { hmWanMbus21 24 }

hmWanMbus21Value09		OBJECT-TYPE
			SYNTAX	INTEGER
			MAX-ACCESS	read-only
			STATUS	current
			::= { hmWanMbus21 25 }

hmWanMbus21VIF0A		OBJECT-TYPE
			SYNTAX	INTEGER
			MAX-ACCESS	read-only
			STATUS	current
			::= { hmWanMbus21 26 }

hmWanMbus21Value0A		OBJECT-TYPE
			SYNTAX	INTEGER
			MAX-ACCESS	read-only
			STATUS	current
			::= { hmWanMbus21 27 }

hmWanMbus21VIF0B		OBJECT-TYPE
			SYNTAX	INTEGER
			MAX-ACCESS	read-only
			STATUS	current
			::= { hmWanMbus21 28 }

hmWanMbus21Value0B		OBJECT-TYPE
			SYNTAX	INTEGER
			MAX-ACCESS	read-only
			STATUS	current
			::= { hmWanMbus21 29 }

hmWanMbus21VIF0C		OBJECT-TYPE
			SYNTAX	INTEGER
			MAX-ACCESS	read-only
			STATUS	current
			::= { hmWanMbus21 30 }

hmWanMbus21Value0C		OBJECT-TYPE
			SYNTAX	INTEGER
			MAX-ACCESS	read-only
			STATUS	current
			::= { hmWanMbus21 31 }

hmWanMbus21VIF0D		OBJECT-TYPE
			SYNTAX	INTEGER
			MAX-ACCESS	read-only
			STATUS	current
			::= { hmWanMbus21 32 }

hmWanMbus21Value0D		OBJECT-TYPE
			SYNTAX	INTEGER
			MAX-ACCESS	read-only
			STATUS	current
			::= { hmWanMbus21 33 }

hmWanMbus21VIF0E		OBJECT-TYPE
			SYNTAX	INTEGER
			MAX-ACCESS	read-only
			STATUS	current
			::= { hmWanMbus21 34 }

hmWanMbus21Value0E		OBJECT-TYPE
			SYNTAX	INTEGER
			MAX-ACCESS	read-only
			STATUS	current
			::= { hmWanMbus21 35 }

hmWanMbus21VIF0F		OBJECT-TYPE
			SYNTAX	INTEGER
			MAX-ACCESS	read-only
			STATUS	current
			::= { hmWanMbus21 36 }

hmWanMbus21Value0F		OBJECT-TYPE
			SYNTAX	INTEGER
			MAX-ACCESS	read-only
			STATUS	current
			::= { hmWanMbus21 37 }

hmWanMbus21VIF10		OBJECT-TYPE
			SYNTAX	INTEGER
			MAX-ACCESS	read-only
			STATUS	current
			::= { hmWanMbus21 38 }

hmWanMbus21Value10		OBJECT-TYPE
			SYNTAX	INTEGER
			MAX-ACCESS	read-only
			STATUS	current
			::= { hmWanMbus21 39 }

hmWanMbus21VIF11		OBJECT-TYPE
			SYNTAX	INTEGER
			MAX-ACCESS	read-only
			STATUS	current
			::= { hmWanMbus21 40 }

hmWanMbus21Value11		OBJECT-TYPE
			SYNTAX	INTEGER
			MAX-ACCESS	read-only
			STATUS	current
			::= { hmWanMbus21 41 }

hmWanMbus21VIF12		OBJECT-TYPE
			SYNTAX	INTEGER
			MAX-ACCESS	read-only
			STATUS	current
			::= { hmWanMbus21 42 }

hmWanMbus21Value12		OBJECT-TYPE
			SYNTAX	INTEGER
			MAX-ACCESS	read-only
			STATUS	current
			::= { hmWanMbus21 43 }

hmWanMbus21VIF13		OBJECT-TYPE
			SYNTAX	INTEGER
			MAX-ACCESS	read-only
			STATUS	current
			::= { hmWanMbus21 44 }

hmWanMbus21Value13		OBJECT-TYPE
			SYNTAX	INTEGER
			MAX-ACCESS	read-only
			STATUS	current
			::= { hmWanMbus21 45 }

hmWanMbus21VIF14		OBJECT-TYPE
			SYNTAX	INTEGER
			MAX-ACCESS	read-only
			STATUS	current
			::= { hmWanMbus21 46 }

hmWanMbus21Value14		OBJECT-TYPE
			SYNTAX	INTEGER
			MAX-ACCESS	read-only
			STATUS	current
			::= { hmWanMbus21 47 }

hmWanMbus21VIF15		OBJECT-TYPE
			SYNTAX	INTEGER
			MAX-ACCESS	read-only
			STATUS	current
			::= { hmWanMbus21 48 }

hmWanMbus21Value15		OBJECT-TYPE
			SYNTAX	INTEGER
			MAX-ACCESS	read-only
			STATUS	current
			::= { hmWanMbus21 49 }

hmWanMbus21VIF16		OBJECT-TYPE
			SYNTAX	INTEGER
			MAX-ACCESS	read-only
			STATUS	current
			::= { hmWanMbus21 50 }

hmWanMbus21Value16		OBJECT-TYPE
			SYNTAX	INTEGER
			MAX-ACCESS	read-only
			STATUS	current
			::= { hmWanMbus21 51 }

hmWanMbus21VIF17		OBJECT-TYPE
			SYNTAX	INTEGER
			MAX-ACCESS	read-only
			STATUS	current
			::= { hmWanMbus21 52 }

hmWanMbus21Value17		OBJECT-TYPE
			SYNTAX	INTEGER
			MAX-ACCESS	read-only
			STATUS	current
			::= { hmWanMbus21 53 }

hmWanMbus21VIF18		OBJECT-TYPE
			SYNTAX	INTEGER
			MAX-ACCESS	read-only
			STATUS	current
			::= { hmWanMbus21 54 }

hmWanMbus21Value18		OBJECT-TYPE
			SYNTAX	INTEGER
			MAX-ACCESS	read-only
			STATUS	current
			::= { hmWanMbus21 55 }

hmWanMbus21VIF19		OBJECT-TYPE
			SYNTAX	INTEGER
			MAX-ACCESS	read-only
			STATUS	current
			::= { hmWanMbus21 56 }

hmWanMbus21Value19		OBJECT-TYPE
			SYNTAX	INTEGER
			MAX-ACCESS	read-only
			STATUS	current
			::= { hmWanMbus21 57 }

hmWanMbus21VIF1A		OBJECT-TYPE
			SYNTAX	INTEGER
			MAX-ACCESS	read-only
			STATUS	current
			::= { hmWanMbus21 58 }

hmWanMbus21Value1A		OBJECT-TYPE
			SYNTAX	INTEGER
			MAX-ACCESS	read-only
			STATUS	current
			::= { hmWanMbus21 59 }

hmWanMbus21VIF1B		OBJECT-TYPE
			SYNTAX	INTEGER
			MAX-ACCESS	read-only
			STATUS	current
			::= { hmWanMbus21 60 }

hmWanMbus21Value1B		OBJECT-TYPE
			SYNTAX	INTEGER
			MAX-ACCESS	read-only
			STATUS	current
			::= { hmWanMbus21 61 }

hmWanMbus21VIF1C		OBJECT-TYPE
			SYNTAX	INTEGER
			MAX-ACCESS	read-only
			STATUS	current
			::= { hmWanMbus21 62 }

hmWanMbus21Value1C		OBJECT-TYPE
			SYNTAX	INTEGER
			MAX-ACCESS	read-only
			STATUS	current
			::= { hmWanMbus21 63 }

hmWanMbus21VIF1D		OBJECT-TYPE
			SYNTAX	INTEGER
			MAX-ACCESS	read-only
			STATUS	current
			::= { hmWanMbus21 64 }

hmWanMbus21Value1D		OBJECT-TYPE
			SYNTAX	INTEGER
			MAX-ACCESS	read-only
			STATUS	current
			::= { hmWanMbus21 65 }

hmWanMbus21VIF1E		OBJECT-TYPE
			SYNTAX	INTEGER
			MAX-ACCESS	read-only
			STATUS	current
			::= { hmWanMbus21 66 }

hmWanMbus21Value1E		OBJECT-TYPE
			SYNTAX	INTEGER
			MAX-ACCESS	read-only
			STATUS	current
			::= { hmWanMbus21 67 }

hmWanMbus21VIF1F		OBJECT-TYPE
			SYNTAX	INTEGER
			MAX-ACCESS	read-only
			STATUS	current
			::= { hmWanMbus21 68 }

hmWanMbus21Value1F		OBJECT-TYPE
			SYNTAX	INTEGER
			MAX-ACCESS	read-only
			STATUS	current
			::= { hmWanMbus21 69 }

hmWanMbus21VIF20		OBJECT-TYPE
			SYNTAX	INTEGER
			MAX-ACCESS	read-only
			STATUS	current
			::= { hmWanMbus21 70 }

hmWanMbus21Value20		OBJECT-TYPE
			SYNTAX	INTEGER
			MAX-ACCESS	read-only
			STATUS	current
			::= { hmWanMbus21 71 }

hmWanMbus21VIF21		OBJECT-TYPE
			SYNTAX	INTEGER
			MAX-ACCESS	read-only
			STATUS	current
			::= { hmWanMbus21 72 }

hmWanMbus21Value21		OBJECT-TYPE
			SYNTAX	INTEGER
			MAX-ACCESS	read-only
			STATUS	current
			::= { hmWanMbus21 73 }

hmWanMbus21VIF22		OBJECT-TYPE
			SYNTAX	INTEGER
			MAX-ACCESS	read-only
			STATUS	current
			::= { hmWanMbus21 74 }

hmWanMbus21Value22		OBJECT-TYPE
			SYNTAX	INTEGER
			MAX-ACCESS	read-only
			STATUS	current
			::= { hmWanMbus21 75 }

hmWanMbus21VIF23		OBJECT-TYPE
			SYNTAX	INTEGER
			MAX-ACCESS	read-only
			STATUS	current
			::= { hmWanMbus21 76 }

hmWanMbus21Value23		OBJECT-TYPE
			SYNTAX	INTEGER
			MAX-ACCESS	read-only
			STATUS	current
			::= { hmWanMbus21 77 }

hmWanMbus21VIF24		OBJECT-TYPE
			SYNTAX	INTEGER
			MAX-ACCESS	read-only
			STATUS	current
			::= { hmWanMbus21 78 }

hmWanMbus21Value24		OBJECT-TYPE
			SYNTAX	INTEGER
			MAX-ACCESS	read-only
			STATUS	current
			::= { hmWanMbus21 79 }

hmWanMbus21VIF25		OBJECT-TYPE
			SYNTAX	INTEGER
			MAX-ACCESS	read-only
			STATUS	current
			::= { hmWanMbus21 80 }

hmWanMbus21Value25		OBJECT-TYPE
			SYNTAX	INTEGER
			MAX-ACCESS	read-only
			STATUS	current
			::= { hmWanMbus21 81 }

hmWanMbus21VIF26		OBJECT-TYPE
			SYNTAX	INTEGER
			MAX-ACCESS	read-only
			STATUS	current
			::= { hmWanMbus21 82 }

hmWanMbus21Value26		OBJECT-TYPE
			SYNTAX	INTEGER
			MAX-ACCESS	read-only
			STATUS	current
			::= { hmWanMbus21 83 }

hmWanMbus21VIF27		OBJECT-TYPE
			SYNTAX	INTEGER
			MAX-ACCESS	read-only
			STATUS	current
			::= { hmWanMbus21 84 }

hmWanMbus21Value27		OBJECT-TYPE
			SYNTAX	INTEGER
			MAX-ACCESS	read-only
			STATUS	current
			::= { hmWanMbus21 85 }

hmWanMbus21VIF28		OBJECT-TYPE
			SYNTAX	INTEGER
			MAX-ACCESS	read-only
			STATUS	current
			::= { hmWanMbus21 86 }

hmWanMbus21Value28		OBJECT-TYPE
			SYNTAX	INTEGER
			MAX-ACCESS	read-only
			STATUS	current
			::= { hmWanMbus21 87 }

hmWanMbus21VIF29		OBJECT-TYPE
			SYNTAX	INTEGER
			MAX-ACCESS	read-only
			STATUS	current
			::= { hmWanMbus21 88 }

hmWanMbus21Value29		OBJECT-TYPE
			SYNTAX	INTEGER
			MAX-ACCESS	read-only
			STATUS	current
			::= { hmWanMbus21 89 }

hmWanMbus21VIF2A		OBJECT-TYPE
			SYNTAX	INTEGER
			MAX-ACCESS	read-only
			STATUS	current
			::= { hmWanMbus21 90 }

hmWanMbus21Value2A		OBJECT-TYPE
			SYNTAX	INTEGER
			MAX-ACCESS	read-only
			STATUS	current
			::= { hmWanMbus21 91 }

hmWanMbus21VIF2B		OBJECT-TYPE
			SYNTAX	INTEGER
			MAX-ACCESS	read-only
			STATUS	current
			::= { hmWanMbus21 92 }

hmWanMbus21Value2B		OBJECT-TYPE
			SYNTAX	INTEGER
			MAX-ACCESS	read-only
			STATUS	current
			::= { hmWanMbus21 93 }

hmWanMbus21VIF2C		OBJECT-TYPE
			SYNTAX	INTEGER
			MAX-ACCESS	read-only
			STATUS	current
			::= { hmWanMbus21 94 }

hmWanMbus21Value2C		OBJECT-TYPE
			SYNTAX	INTEGER
			MAX-ACCESS	read-only
			STATUS	current
			::= { hmWanMbus21 95 }

hmWanMbus21VIF2D		OBJECT-TYPE
			SYNTAX	INTEGER
			MAX-ACCESS	read-only
			STATUS	current
			::= { hmWanMbus21 96 }

hmWanMbus21Value2D		OBJECT-TYPE
			SYNTAX	INTEGER
			MAX-ACCESS	read-only
			STATUS	current
			::= { hmWanMbus21 97 }

hmWanMbus21VIF2E		OBJECT-TYPE
			SYNTAX	INTEGER
			MAX-ACCESS	read-only
			STATUS	current
			::= { hmWanMbus21 98 }

hmWanMbus21Value2E		OBJECT-TYPE
			SYNTAX	INTEGER
			MAX-ACCESS	read-only
			STATUS	current
			::= { hmWanMbus21 99 }

hmWanMbus21VIF2F		OBJECT-TYPE
			SYNTAX	INTEGER
			MAX-ACCESS	read-only
			STATUS	current
			::= { hmWanMbus21 100 }

hmWanMbus21Value2F		OBJECT-TYPE
			SYNTAX	INTEGER
			MAX-ACCESS	read-only
			STATUS	current
			::= { hmWanMbus21 101 }

hmWanMbus22			OBJECT IDENTIFIER ::= { hmWanMbus 34 }

hmWanMbus22IdNumber		OBJECT-TYPE
			SYNTAX	Gauge32
			MAX-ACCESS	read-only
			STATUS	current
			::= { hmWanMbus22 1 }

hmWanMbus22Manufacturer	OBJECT-TYPE
			SYNTAX	Gauge32
			MAX-ACCESS	read-only
			STATUS	current
			::= { hmWanMbus22 2 }

hmWanMbus22Version		OBJECT-TYPE
			SYNTAX	Gauge32
			MAX-ACCESS	read-only
			STATUS	current
			::= { hmWanMbus22 3 }

hmWanMbus22Medium		OBJECT-TYPE
			SYNTAX	Gauge32
			MAX-ACCESS	read-only
			STATUS	current
			::= { hmWanMbus22 4 }

hmWanMbus22Status		OBJECT-TYPE
			SYNTAX	Gauge32
			MAX-ACCESS	read-only
			STATUS	current
			::= { hmWanMbus22 5 }

hmWanMbus22VIF00		OBJECT-TYPE
			SYNTAX	INTEGER
			MAX-ACCESS	read-only
			STATUS	current
			::= { hmWanMbus22 6 }

hmWanMbus22Value00		OBJECT-TYPE
			SYNTAX	INTEGER
			MAX-ACCESS	read-only
			STATUS	current
			::= { hmWanMbus22 7 }

hmWanMbus22VIF01		OBJECT-TYPE
			SYNTAX	INTEGER
			MAX-ACCESS	read-only
			STATUS	current
			::= { hmWanMbus22 8 }

hmWanMbus22Value01		OBJECT-TYPE
			SYNTAX	INTEGER
			MAX-ACCESS	read-only
			STATUS	current
			::= { hmWanMbus22 9 }

hmWanMbus22VIF02		OBJECT-TYPE
			SYNTAX	INTEGER
			MAX-ACCESS	read-only
			STATUS	current
			::= { hmWanMbus22 10 }

hmWanMbus22Value02		OBJECT-TYPE
			SYNTAX	INTEGER
			MAX-ACCESS	read-only
			STATUS	current
			::= { hmWanMbus22 11 }

hmWanMbus22VIF03		OBJECT-TYPE
			SYNTAX	INTEGER
			MAX-ACCESS	read-only
			STATUS	current
			::= { hmWanMbus22 12 }

hmWanMbus22Value03		OBJECT-TYPE
			SYNTAX	INTEGER
			MAX-ACCESS	read-only
			STATUS	current
			::= { hmWanMbus22 13 }

hmWanMbus22VIF04		OBJECT-TYPE
			SYNTAX	INTEGER
			MAX-ACCESS	read-only
			STATUS	current
			::= { hmWanMbus22 14 }

hmWanMbus22Value04		OBJECT-TYPE
			SYNTAX	INTEGER
			MAX-ACCESS	read-only
			STATUS	current
			::= { hmWanMbus22 15 }

hmWanMbus22VIF05		OBJECT-TYPE
			SYNTAX	INTEGER
			MAX-ACCESS	read-only
			STATUS	current
			::= { hmWanMbus22 16 }

hmWanMbus22Value05		OBJECT-TYPE
			SYNTAX	INTEGER
			MAX-ACCESS	read-only
			STATUS	current
			::= { hmWanMbus22 17 }

hmWanMbus22VIF06		OBJECT-TYPE
			SYNTAX	INTEGER
			MAX-ACCESS	read-only
			STATUS	current
			::= { hmWanMbus22 18 }

hmWanMbus22Value06		OBJECT-TYPE
			SYNTAX	INTEGER
			MAX-ACCESS	read-only
			STATUS	current
			::= { hmWanMbus22 19 }

hmWanMbus22VIF07		OBJECT-TYPE
			SYNTAX	INTEGER
			MAX-ACCESS	read-only
			STATUS	current
			::= { hmWanMbus22 20 }

hmWanMbus22Value07		OBJECT-TYPE
			SYNTAX	INTEGER
			MAX-ACCESS	read-only
			STATUS	current
			::= { hmWanMbus22 21 }

hmWanMbus22VIF08		OBJECT-TYPE
			SYNTAX	INTEGER
			MAX-ACCESS	read-only
			STATUS	current
			::= { hmWanMbus22 22 }

hmWanMbus22Value08		OBJECT-TYPE
			SYNTAX	INTEGER
			MAX-ACCESS	read-only
			STATUS	current
			::= { hmWanMbus22 23 }

hmWanMbus22VIF09		OBJECT-TYPE
			SYNTAX	INTEGER
			MAX-ACCESS	read-only
			STATUS	current
			::= { hmWanMbus22 24 }

hmWanMbus22Value09		OBJECT-TYPE
			SYNTAX	INTEGER
			MAX-ACCESS	read-only
			STATUS	current
			::= { hmWanMbus22 25 }

hmWanMbus22VIF0A		OBJECT-TYPE
			SYNTAX	INTEGER
			MAX-ACCESS	read-only
			STATUS	current
			::= { hmWanMbus22 26 }

hmWanMbus22Value0A		OBJECT-TYPE
			SYNTAX	INTEGER
			MAX-ACCESS	read-only
			STATUS	current
			::= { hmWanMbus22 27 }

hmWanMbus22VIF0B		OBJECT-TYPE
			SYNTAX	INTEGER
			MAX-ACCESS	read-only
			STATUS	current
			::= { hmWanMbus22 28 }

hmWanMbus22Value0B		OBJECT-TYPE
			SYNTAX	INTEGER
			MAX-ACCESS	read-only
			STATUS	current
			::= { hmWanMbus22 29 }

hmWanMbus22VIF0C		OBJECT-TYPE
			SYNTAX	INTEGER
			MAX-ACCESS	read-only
			STATUS	current
			::= { hmWanMbus22 30 }

hmWanMbus22Value0C		OBJECT-TYPE
			SYNTAX	INTEGER
			MAX-ACCESS	read-only
			STATUS	current
			::= { hmWanMbus22 31 }

hmWanMbus22VIF0D		OBJECT-TYPE
			SYNTAX	INTEGER
			MAX-ACCESS	read-only
			STATUS	current
			::= { hmWanMbus22 32 }

hmWanMbus22Value0D		OBJECT-TYPE
			SYNTAX	INTEGER
			MAX-ACCESS	read-only
			STATUS	current
			::= { hmWanMbus22 33 }

hmWanMbus22VIF0E		OBJECT-TYPE
			SYNTAX	INTEGER
			MAX-ACCESS	read-only
			STATUS	current
			::= { hmWanMbus22 34 }

hmWanMbus22Value0E		OBJECT-TYPE
			SYNTAX	INTEGER
			MAX-ACCESS	read-only
			STATUS	current
			::= { hmWanMbus22 35 }

hmWanMbus22VIF0F		OBJECT-TYPE
			SYNTAX	INTEGER
			MAX-ACCESS	read-only
			STATUS	current
			::= { hmWanMbus22 36 }

hmWanMbus22Value0F		OBJECT-TYPE
			SYNTAX	INTEGER
			MAX-ACCESS	read-only
			STATUS	current
			::= { hmWanMbus22 37 }

hmWanMbus22VIF10		OBJECT-TYPE
			SYNTAX	INTEGER
			MAX-ACCESS	read-only
			STATUS	current
			::= { hmWanMbus22 38 }

hmWanMbus22Value10		OBJECT-TYPE
			SYNTAX	INTEGER
			MAX-ACCESS	read-only
			STATUS	current
			::= { hmWanMbus22 39 }

hmWanMbus22VIF11		OBJECT-TYPE
			SYNTAX	INTEGER
			MAX-ACCESS	read-only
			STATUS	current
			::= { hmWanMbus22 40 }

hmWanMbus22Value11		OBJECT-TYPE
			SYNTAX	INTEGER
			MAX-ACCESS	read-only
			STATUS	current
			::= { hmWanMbus22 41 }

hmWanMbus22VIF12		OBJECT-TYPE
			SYNTAX	INTEGER
			MAX-ACCESS	read-only
			STATUS	current
			::= { hmWanMbus22 42 }

hmWanMbus22Value12		OBJECT-TYPE
			SYNTAX	INTEGER
			MAX-ACCESS	read-only
			STATUS	current
			::= { hmWanMbus22 43 }

hmWanMbus22VIF13		OBJECT-TYPE
			SYNTAX	INTEGER
			MAX-ACCESS	read-only
			STATUS	current
			::= { hmWanMbus22 44 }

hmWanMbus22Value13		OBJECT-TYPE
			SYNTAX	INTEGER
			MAX-ACCESS	read-only
			STATUS	current
			::= { hmWanMbus22 45 }

hmWanMbus22VIF14		OBJECT-TYPE
			SYNTAX	INTEGER
			MAX-ACCESS	read-only
			STATUS	current
			::= { hmWanMbus22 46 }

hmWanMbus22Value14		OBJECT-TYPE
			SYNTAX	INTEGER
			MAX-ACCESS	read-only
			STATUS	current
			::= { hmWanMbus22 47 }

hmWanMbus22VIF15		OBJECT-TYPE
			SYNTAX	INTEGER
			MAX-ACCESS	read-only
			STATUS	current
			::= { hmWanMbus22 48 }

hmWanMbus22Value15		OBJECT-TYPE
			SYNTAX	INTEGER
			MAX-ACCESS	read-only
			STATUS	current
			::= { hmWanMbus22 49 }

hmWanMbus22VIF16		OBJECT-TYPE
			SYNTAX	INTEGER
			MAX-ACCESS	read-only
			STATUS	current
			::= { hmWanMbus22 50 }

hmWanMbus22Value16		OBJECT-TYPE
			SYNTAX	INTEGER
			MAX-ACCESS	read-only
			STATUS	current
			::= { hmWanMbus22 51 }

hmWanMbus22VIF17		OBJECT-TYPE
			SYNTAX	INTEGER
			MAX-ACCESS	read-only
			STATUS	current
			::= { hmWanMbus22 52 }

hmWanMbus22Value17		OBJECT-TYPE
			SYNTAX	INTEGER
			MAX-ACCESS	read-only
			STATUS	current
			::= { hmWanMbus22 53 }

hmWanMbus22VIF18		OBJECT-TYPE
			SYNTAX	INTEGER
			MAX-ACCESS	read-only
			STATUS	current
			::= { hmWanMbus22 54 }

hmWanMbus22Value18		OBJECT-TYPE
			SYNTAX	INTEGER
			MAX-ACCESS	read-only
			STATUS	current
			::= { hmWanMbus22 55 }

hmWanMbus22VIF19		OBJECT-TYPE
			SYNTAX	INTEGER
			MAX-ACCESS	read-only
			STATUS	current
			::= { hmWanMbus22 56 }

hmWanMbus22Value19		OBJECT-TYPE
			SYNTAX	INTEGER
			MAX-ACCESS	read-only
			STATUS	current
			::= { hmWanMbus22 57 }

hmWanMbus22VIF1A		OBJECT-TYPE
			SYNTAX	INTEGER
			MAX-ACCESS	read-only
			STATUS	current
			::= { hmWanMbus22 58 }

hmWanMbus22Value1A		OBJECT-TYPE
			SYNTAX	INTEGER
			MAX-ACCESS	read-only
			STATUS	current
			::= { hmWanMbus22 59 }

hmWanMbus22VIF1B		OBJECT-TYPE
			SYNTAX	INTEGER
			MAX-ACCESS	read-only
			STATUS	current
			::= { hmWanMbus22 60 }

hmWanMbus22Value1B		OBJECT-TYPE
			SYNTAX	INTEGER
			MAX-ACCESS	read-only
			STATUS	current
			::= { hmWanMbus22 61 }

hmWanMbus22VIF1C		OBJECT-TYPE
			SYNTAX	INTEGER
			MAX-ACCESS	read-only
			STATUS	current
			::= { hmWanMbus22 62 }

hmWanMbus22Value1C		OBJECT-TYPE
			SYNTAX	INTEGER
			MAX-ACCESS	read-only
			STATUS	current
			::= { hmWanMbus22 63 }

hmWanMbus22VIF1D		OBJECT-TYPE
			SYNTAX	INTEGER
			MAX-ACCESS	read-only
			STATUS	current
			::= { hmWanMbus22 64 }

hmWanMbus22Value1D		OBJECT-TYPE
			SYNTAX	INTEGER
			MAX-ACCESS	read-only
			STATUS	current
			::= { hmWanMbus22 65 }

hmWanMbus22VIF1E		OBJECT-TYPE
			SYNTAX	INTEGER
			MAX-ACCESS	read-only
			STATUS	current
			::= { hmWanMbus22 66 }

hmWanMbus22Value1E		OBJECT-TYPE
			SYNTAX	INTEGER
			MAX-ACCESS	read-only
			STATUS	current
			::= { hmWanMbus22 67 }

hmWanMbus22VIF1F		OBJECT-TYPE
			SYNTAX	INTEGER
			MAX-ACCESS	read-only
			STATUS	current
			::= { hmWanMbus22 68 }

hmWanMbus22Value1F		OBJECT-TYPE
			SYNTAX	INTEGER
			MAX-ACCESS	read-only
			STATUS	current
			::= { hmWanMbus22 69 }

hmWanMbus22VIF20		OBJECT-TYPE
			SYNTAX	INTEGER
			MAX-ACCESS	read-only
			STATUS	current
			::= { hmWanMbus22 70 }

hmWanMbus22Value20		OBJECT-TYPE
			SYNTAX	INTEGER
			MAX-ACCESS	read-only
			STATUS	current
			::= { hmWanMbus22 71 }

hmWanMbus22VIF21		OBJECT-TYPE
			SYNTAX	INTEGER
			MAX-ACCESS	read-only
			STATUS	current
			::= { hmWanMbus22 72 }

hmWanMbus22Value21		OBJECT-TYPE
			SYNTAX	INTEGER
			MAX-ACCESS	read-only
			STATUS	current
			::= { hmWanMbus22 73 }

hmWanMbus22VIF22		OBJECT-TYPE
			SYNTAX	INTEGER
			MAX-ACCESS	read-only
			STATUS	current
			::= { hmWanMbus22 74 }

hmWanMbus22Value22		OBJECT-TYPE
			SYNTAX	INTEGER
			MAX-ACCESS	read-only
			STATUS	current
			::= { hmWanMbus22 75 }

hmWanMbus22VIF23		OBJECT-TYPE
			SYNTAX	INTEGER
			MAX-ACCESS	read-only
			STATUS	current
			::= { hmWanMbus22 76 }

hmWanMbus22Value23		OBJECT-TYPE
			SYNTAX	INTEGER
			MAX-ACCESS	read-only
			STATUS	current
			::= { hmWanMbus22 77 }

hmWanMbus22VIF24		OBJECT-TYPE
			SYNTAX	INTEGER
			MAX-ACCESS	read-only
			STATUS	current
			::= { hmWanMbus22 78 }

hmWanMbus22Value24		OBJECT-TYPE
			SYNTAX	INTEGER
			MAX-ACCESS	read-only
			STATUS	current
			::= { hmWanMbus22 79 }

hmWanMbus22VIF25		OBJECT-TYPE
			SYNTAX	INTEGER
			MAX-ACCESS	read-only
			STATUS	current
			::= { hmWanMbus22 80 }

hmWanMbus22Value25		OBJECT-TYPE
			SYNTAX	INTEGER
			MAX-ACCESS	read-only
			STATUS	current
			::= { hmWanMbus22 81 }

hmWanMbus22VIF26		OBJECT-TYPE
			SYNTAX	INTEGER
			MAX-ACCESS	read-only
			STATUS	current
			::= { hmWanMbus22 82 }

hmWanMbus22Value26		OBJECT-TYPE
			SYNTAX	INTEGER
			MAX-ACCESS	read-only
			STATUS	current
			::= { hmWanMbus22 83 }

hmWanMbus22VIF27		OBJECT-TYPE
			SYNTAX	INTEGER
			MAX-ACCESS	read-only
			STATUS	current
			::= { hmWanMbus22 84 }

hmWanMbus22Value27		OBJECT-TYPE
			SYNTAX	INTEGER
			MAX-ACCESS	read-only
			STATUS	current
			::= { hmWanMbus22 85 }

hmWanMbus22VIF28		OBJECT-TYPE
			SYNTAX	INTEGER
			MAX-ACCESS	read-only
			STATUS	current
			::= { hmWanMbus22 86 }

hmWanMbus22Value28		OBJECT-TYPE
			SYNTAX	INTEGER
			MAX-ACCESS	read-only
			STATUS	current
			::= { hmWanMbus22 87 }

hmWanMbus22VIF29		OBJECT-TYPE
			SYNTAX	INTEGER
			MAX-ACCESS	read-only
			STATUS	current
			::= { hmWanMbus22 88 }

hmWanMbus22Value29		OBJECT-TYPE
			SYNTAX	INTEGER
			MAX-ACCESS	read-only
			STATUS	current
			::= { hmWanMbus22 89 }

hmWanMbus22VIF2A		OBJECT-TYPE
			SYNTAX	INTEGER
			MAX-ACCESS	read-only
			STATUS	current
			::= { hmWanMbus22 90 }

hmWanMbus22Value2A		OBJECT-TYPE
			SYNTAX	INTEGER
			MAX-ACCESS	read-only
			STATUS	current
			::= { hmWanMbus22 91 }

hmWanMbus22VIF2B		OBJECT-TYPE
			SYNTAX	INTEGER
			MAX-ACCESS	read-only
			STATUS	current
			::= { hmWanMbus22 92 }

hmWanMbus22Value2B		OBJECT-TYPE
			SYNTAX	INTEGER
			MAX-ACCESS	read-only
			STATUS	current
			::= { hmWanMbus22 93 }

hmWanMbus22VIF2C		OBJECT-TYPE
			SYNTAX	INTEGER
			MAX-ACCESS	read-only
			STATUS	current
			::= { hmWanMbus22 94 }

hmWanMbus22Value2C		OBJECT-TYPE
			SYNTAX	INTEGER
			MAX-ACCESS	read-only
			STATUS	current
			::= { hmWanMbus22 95 }

hmWanMbus22VIF2D		OBJECT-TYPE
			SYNTAX	INTEGER
			MAX-ACCESS	read-only
			STATUS	current
			::= { hmWanMbus22 96 }

hmWanMbus22Value2D		OBJECT-TYPE
			SYNTAX	INTEGER
			MAX-ACCESS	read-only
			STATUS	current
			::= { hmWanMbus22 97 }

hmWanMbus22VIF2E		OBJECT-TYPE
			SYNTAX	INTEGER
			MAX-ACCESS	read-only
			STATUS	current
			::= { hmWanMbus22 98 }

hmWanMbus22Value2E		OBJECT-TYPE
			SYNTAX	INTEGER
			MAX-ACCESS	read-only
			STATUS	current
			::= { hmWanMbus22 99 }

hmWanMbus22VIF2F		OBJECT-TYPE
			SYNTAX	INTEGER
			MAX-ACCESS	read-only
			STATUS	current
			::= { hmWanMbus22 100 }

hmWanMbus22Value2F		OBJECT-TYPE
			SYNTAX	INTEGER
			MAX-ACCESS	read-only
			STATUS	current
			::= { hmWanMbus22 101 }

hmWanMbus23			OBJECT IDENTIFIER ::= { hmWanMbus 35 }

hmWanMbus23IdNumber		OBJECT-TYPE
			SYNTAX	Gauge32
			MAX-ACCESS	read-only
			STATUS	current
			::= { hmWanMbus23 1 }

hmWanMbus23Manufacturer	OBJECT-TYPE
			SYNTAX	Gauge32
			MAX-ACCESS	read-only
			STATUS	current
			::= { hmWanMbus23 2 }

hmWanMbus23Version		OBJECT-TYPE
			SYNTAX	Gauge32
			MAX-ACCESS	read-only
			STATUS	current
			::= { hmWanMbus23 3 }

hmWanMbus23Medium		OBJECT-TYPE
			SYNTAX	Gauge32
			MAX-ACCESS	read-only
			STATUS	current
			::= { hmWanMbus23 4 }

hmWanMbus23Status		OBJECT-TYPE
			SYNTAX	Gauge32
			MAX-ACCESS	read-only
			STATUS	current
			::= { hmWanMbus23 5 }

hmWanMbus23VIF00		OBJECT-TYPE
			SYNTAX	INTEGER
			MAX-ACCESS	read-only
			STATUS	current
			::= { hmWanMbus23 6 }

hmWanMbus23Value00		OBJECT-TYPE
			SYNTAX	INTEGER
			MAX-ACCESS	read-only
			STATUS	current
			::= { hmWanMbus23 7 }

hmWanMbus23VIF01		OBJECT-TYPE
			SYNTAX	INTEGER
			MAX-ACCESS	read-only
			STATUS	current
			::= { hmWanMbus23 8 }

hmWanMbus23Value01		OBJECT-TYPE
			SYNTAX	INTEGER
			MAX-ACCESS	read-only
			STATUS	current
			::= { hmWanMbus23 9 }

hmWanMbus23VIF02		OBJECT-TYPE
			SYNTAX	INTEGER
			MAX-ACCESS	read-only
			STATUS	current
			::= { hmWanMbus23 10 }

hmWanMbus23Value02		OBJECT-TYPE
			SYNTAX	INTEGER
			MAX-ACCESS	read-only
			STATUS	current
			::= { hmWanMbus23 11 }

hmWanMbus23VIF03		OBJECT-TYPE
			SYNTAX	INTEGER
			MAX-ACCESS	read-only
			STATUS	current
			::= { hmWanMbus23 12 }

hmWanMbus23Value03		OBJECT-TYPE
			SYNTAX	INTEGER
			MAX-ACCESS	read-only
			STATUS	current
			::= { hmWanMbus23 13 }

hmWanMbus23VIF04		OBJECT-TYPE
			SYNTAX	INTEGER
			MAX-ACCESS	read-only
			STATUS	current
			::= { hmWanMbus23 14 }

hmWanMbus23Value04		OBJECT-TYPE
			SYNTAX	INTEGER
			MAX-ACCESS	read-only
			STATUS	current
			::= { hmWanMbus23 15 }

hmWanMbus23VIF05		OBJECT-TYPE
			SYNTAX	INTEGER
			MAX-ACCESS	read-only
			STATUS	current
			::= { hmWanMbus23 16 }

hmWanMbus23Value05		OBJECT-TYPE
			SYNTAX	INTEGER
			MAX-ACCESS	read-only
			STATUS	current
			::= { hmWanMbus23 17 }

hmWanMbus23VIF06		OBJECT-TYPE
			SYNTAX	INTEGER
			MAX-ACCESS	read-only
			STATUS	current
			::= { hmWanMbus23 18 }

hmWanMbus23Value06		OBJECT-TYPE
			SYNTAX	INTEGER
			MAX-ACCESS	read-only
			STATUS	current
			::= { hmWanMbus23 19 }

hmWanMbus23VIF07		OBJECT-TYPE
			SYNTAX	INTEGER
			MAX-ACCESS	read-only
			STATUS	current
			::= { hmWanMbus23 20 }

hmWanMbus23Value07		OBJECT-TYPE
			SYNTAX	INTEGER
			MAX-ACCESS	read-only
			STATUS	current
			::= { hmWanMbus23 21 }

hmWanMbus23VIF08		OBJECT-TYPE
			SYNTAX	INTEGER
			MAX-ACCESS	read-only
			STATUS	current
			::= { hmWanMbus23 22 }

hmWanMbus23Value08		OBJECT-TYPE
			SYNTAX	INTEGER
			MAX-ACCESS	read-only
			STATUS	current
			::= { hmWanMbus23 23 }

hmWanMbus23VIF09		OBJECT-TYPE
			SYNTAX	INTEGER
			MAX-ACCESS	read-only
			STATUS	current
			::= { hmWanMbus23 24 }

hmWanMbus23Value09		OBJECT-TYPE
			SYNTAX	INTEGER
			MAX-ACCESS	read-only
			STATUS	current
			::= { hmWanMbus23 25 }

hmWanMbus23VIF0A		OBJECT-TYPE
			SYNTAX	INTEGER
			MAX-ACCESS	read-only
			STATUS	current
			::= { hmWanMbus23 26 }

hmWanMbus23Value0A		OBJECT-TYPE
			SYNTAX	INTEGER
			MAX-ACCESS	read-only
			STATUS	current
			::= { hmWanMbus23 27 }

hmWanMbus23VIF0B		OBJECT-TYPE
			SYNTAX	INTEGER
			MAX-ACCESS	read-only
			STATUS	current
			::= { hmWanMbus23 28 }

hmWanMbus23Value0B		OBJECT-TYPE
			SYNTAX	INTEGER
			MAX-ACCESS	read-only
			STATUS	current
			::= { hmWanMbus23 29 }

hmWanMbus23VIF0C		OBJECT-TYPE
			SYNTAX	INTEGER
			MAX-ACCESS	read-only
			STATUS	current
			::= { hmWanMbus23 30 }

hmWanMbus23Value0C		OBJECT-TYPE
			SYNTAX	INTEGER
			MAX-ACCESS	read-only
			STATUS	current
			::= { hmWanMbus23 31 }

hmWanMbus23VIF0D		OBJECT-TYPE
			SYNTAX	INTEGER
			MAX-ACCESS	read-only
			STATUS	current
			::= { hmWanMbus23 32 }

hmWanMbus23Value0D		OBJECT-TYPE
			SYNTAX	INTEGER
			MAX-ACCESS	read-only
			STATUS	current
			::= { hmWanMbus23 33 }

hmWanMbus23VIF0E		OBJECT-TYPE
			SYNTAX	INTEGER
			MAX-ACCESS	read-only
			STATUS	current
			::= { hmWanMbus23 34 }

hmWanMbus23Value0E		OBJECT-TYPE
			SYNTAX	INTEGER
			MAX-ACCESS	read-only
			STATUS	current
			::= { hmWanMbus23 35 }

hmWanMbus23VIF0F		OBJECT-TYPE
			SYNTAX	INTEGER
			MAX-ACCESS	read-only
			STATUS	current
			::= { hmWanMbus23 36 }

hmWanMbus23Value0F		OBJECT-TYPE
			SYNTAX	INTEGER
			MAX-ACCESS	read-only
			STATUS	current
			::= { hmWanMbus23 37 }

hmWanMbus23VIF10		OBJECT-TYPE
			SYNTAX	INTEGER
			MAX-ACCESS	read-only
			STATUS	current
			::= { hmWanMbus23 38 }

hmWanMbus23Value10		OBJECT-TYPE
			SYNTAX	INTEGER
			MAX-ACCESS	read-only
			STATUS	current
			::= { hmWanMbus23 39 }

hmWanMbus23VIF11		OBJECT-TYPE
			SYNTAX	INTEGER
			MAX-ACCESS	read-only
			STATUS	current
			::= { hmWanMbus23 40 }

hmWanMbus23Value11		OBJECT-TYPE
			SYNTAX	INTEGER
			MAX-ACCESS	read-only
			STATUS	current
			::= { hmWanMbus23 41 }

hmWanMbus23VIF12		OBJECT-TYPE
			SYNTAX	INTEGER
			MAX-ACCESS	read-only
			STATUS	current
			::= { hmWanMbus23 42 }

hmWanMbus23Value12		OBJECT-TYPE
			SYNTAX	INTEGER
			MAX-ACCESS	read-only
			STATUS	current
			::= { hmWanMbus23 43 }

hmWanMbus23VIF13		OBJECT-TYPE
			SYNTAX	INTEGER
			MAX-ACCESS	read-only
			STATUS	current
			::= { hmWanMbus23 44 }

hmWanMbus23Value13		OBJECT-TYPE
			SYNTAX	INTEGER
			MAX-ACCESS	read-only
			STATUS	current
			::= { hmWanMbus23 45 }

hmWanMbus23VIF14		OBJECT-TYPE
			SYNTAX	INTEGER
			MAX-ACCESS	read-only
			STATUS	current
			::= { hmWanMbus23 46 }

hmWanMbus23Value14		OBJECT-TYPE
			SYNTAX	INTEGER
			MAX-ACCESS	read-only
			STATUS	current
			::= { hmWanMbus23 47 }

hmWanMbus23VIF15		OBJECT-TYPE
			SYNTAX	INTEGER
			MAX-ACCESS	read-only
			STATUS	current
			::= { hmWanMbus23 48 }

hmWanMbus23Value15		OBJECT-TYPE
			SYNTAX	INTEGER
			MAX-ACCESS	read-only
			STATUS	current
			::= { hmWanMbus23 49 }

hmWanMbus23VIF16		OBJECT-TYPE
			SYNTAX	INTEGER
			MAX-ACCESS	read-only
			STATUS	current
			::= { hmWanMbus23 50 }

hmWanMbus23Value16		OBJECT-TYPE
			SYNTAX	INTEGER
			MAX-ACCESS	read-only
			STATUS	current
			::= { hmWanMbus23 51 }

hmWanMbus23VIF17		OBJECT-TYPE
			SYNTAX	INTEGER
			MAX-ACCESS	read-only
			STATUS	current
			::= { hmWanMbus23 52 }

hmWanMbus23Value17		OBJECT-TYPE
			SYNTAX	INTEGER
			MAX-ACCESS	read-only
			STATUS	current
			::= { hmWanMbus23 53 }

hmWanMbus23VIF18		OBJECT-TYPE
			SYNTAX	INTEGER
			MAX-ACCESS	read-only
			STATUS	current
			::= { hmWanMbus23 54 }

hmWanMbus23Value18		OBJECT-TYPE
			SYNTAX	INTEGER
			MAX-ACCESS	read-only
			STATUS	current
			::= { hmWanMbus23 55 }

hmWanMbus23VIF19		OBJECT-TYPE
			SYNTAX	INTEGER
			MAX-ACCESS	read-only
			STATUS	current
			::= { hmWanMbus23 56 }

hmWanMbus23Value19		OBJECT-TYPE
			SYNTAX	INTEGER
			MAX-ACCESS	read-only
			STATUS	current
			::= { hmWanMbus23 57 }

hmWanMbus23VIF1A		OBJECT-TYPE
			SYNTAX	INTEGER
			MAX-ACCESS	read-only
			STATUS	current
			::= { hmWanMbus23 58 }

hmWanMbus23Value1A		OBJECT-TYPE
			SYNTAX	INTEGER
			MAX-ACCESS	read-only
			STATUS	current
			::= { hmWanMbus23 59 }

hmWanMbus23VIF1B		OBJECT-TYPE
			SYNTAX	INTEGER
			MAX-ACCESS	read-only
			STATUS	current
			::= { hmWanMbus23 60 }

hmWanMbus23Value1B		OBJECT-TYPE
			SYNTAX	INTEGER
			MAX-ACCESS	read-only
			STATUS	current
			::= { hmWanMbus23 61 }

hmWanMbus23VIF1C		OBJECT-TYPE
			SYNTAX	INTEGER
			MAX-ACCESS	read-only
			STATUS	current
			::= { hmWanMbus23 62 }

hmWanMbus23Value1C		OBJECT-TYPE
			SYNTAX	INTEGER
			MAX-ACCESS	read-only
			STATUS	current
			::= { hmWanMbus23 63 }

hmWanMbus23VIF1D		OBJECT-TYPE
			SYNTAX	INTEGER
			MAX-ACCESS	read-only
			STATUS	current
			::= { hmWanMbus23 64 }

hmWanMbus23Value1D		OBJECT-TYPE
			SYNTAX	INTEGER
			MAX-ACCESS	read-only
			STATUS	current
			::= { hmWanMbus23 65 }

hmWanMbus23VIF1E		OBJECT-TYPE
			SYNTAX	INTEGER
			MAX-ACCESS	read-only
			STATUS	current
			::= { hmWanMbus23 66 }

hmWanMbus23Value1E		OBJECT-TYPE
			SYNTAX	INTEGER
			MAX-ACCESS	read-only
			STATUS	current
			::= { hmWanMbus23 67 }

hmWanMbus23VIF1F		OBJECT-TYPE
			SYNTAX	INTEGER
			MAX-ACCESS	read-only
			STATUS	current
			::= { hmWanMbus23 68 }

hmWanMbus23Value1F		OBJECT-TYPE
			SYNTAX	INTEGER
			MAX-ACCESS	read-only
			STATUS	current
			::= { hmWanMbus23 69 }

hmWanMbus23VIF20		OBJECT-TYPE
			SYNTAX	INTEGER
			MAX-ACCESS	read-only
			STATUS	current
			::= { hmWanMbus23 70 }

hmWanMbus23Value20		OBJECT-TYPE
			SYNTAX	INTEGER
			MAX-ACCESS	read-only
			STATUS	current
			::= { hmWanMbus23 71 }

hmWanMbus23VIF21		OBJECT-TYPE
			SYNTAX	INTEGER
			MAX-ACCESS	read-only
			STATUS	current
			::= { hmWanMbus23 72 }

hmWanMbus23Value21		OBJECT-TYPE
			SYNTAX	INTEGER
			MAX-ACCESS	read-only
			STATUS	current
			::= { hmWanMbus23 73 }

hmWanMbus23VIF22		OBJECT-TYPE
			SYNTAX	INTEGER
			MAX-ACCESS	read-only
			STATUS	current
			::= { hmWanMbus23 74 }

hmWanMbus23Value22		OBJECT-TYPE
			SYNTAX	INTEGER
			MAX-ACCESS	read-only
			STATUS	current
			::= { hmWanMbus23 75 }

hmWanMbus23VIF23		OBJECT-TYPE
			SYNTAX	INTEGER
			MAX-ACCESS	read-only
			STATUS	current
			::= { hmWanMbus23 76 }

hmWanMbus23Value23		OBJECT-TYPE
			SYNTAX	INTEGER
			MAX-ACCESS	read-only
			STATUS	current
			::= { hmWanMbus23 77 }

hmWanMbus23VIF24		OBJECT-TYPE
			SYNTAX	INTEGER
			MAX-ACCESS	read-only
			STATUS	current
			::= { hmWanMbus23 78 }

hmWanMbus23Value24		OBJECT-TYPE
			SYNTAX	INTEGER
			MAX-ACCESS	read-only
			STATUS	current
			::= { hmWanMbus23 79 }

hmWanMbus23VIF25		OBJECT-TYPE
			SYNTAX	INTEGER
			MAX-ACCESS	read-only
			STATUS	current
			::= { hmWanMbus23 80 }

hmWanMbus23Value25		OBJECT-TYPE
			SYNTAX	INTEGER
			MAX-ACCESS	read-only
			STATUS	current
			::= { hmWanMbus23 81 }

hmWanMbus23VIF26		OBJECT-TYPE
			SYNTAX	INTEGER
			MAX-ACCESS	read-only
			STATUS	current
			::= { hmWanMbus23 82 }

hmWanMbus23Value26		OBJECT-TYPE
			SYNTAX	INTEGER
			MAX-ACCESS	read-only
			STATUS	current
			::= { hmWanMbus23 83 }

hmWanMbus23VIF27		OBJECT-TYPE
			SYNTAX	INTEGER
			MAX-ACCESS	read-only
			STATUS	current
			::= { hmWanMbus23 84 }

hmWanMbus23Value27		OBJECT-TYPE
			SYNTAX	INTEGER
			MAX-ACCESS	read-only
			STATUS	current
			::= { hmWanMbus23 85 }

hmWanMbus23VIF28		OBJECT-TYPE
			SYNTAX	INTEGER
			MAX-ACCESS	read-only
			STATUS	current
			::= { hmWanMbus23 86 }

hmWanMbus23Value28		OBJECT-TYPE
			SYNTAX	INTEGER
			MAX-ACCESS	read-only
			STATUS	current
			::= { hmWanMbus23 87 }

hmWanMbus23VIF29		OBJECT-TYPE
			SYNTAX	INTEGER
			MAX-ACCESS	read-only
			STATUS	current
			::= { hmWanMbus23 88 }

hmWanMbus23Value29		OBJECT-TYPE
			SYNTAX	INTEGER
			MAX-ACCESS	read-only
			STATUS	current
			::= { hmWanMbus23 89 }

hmWanMbus23VIF2A		OBJECT-TYPE
			SYNTAX	INTEGER
			MAX-ACCESS	read-only
			STATUS	current
			::= { hmWanMbus23 90 }

hmWanMbus23Value2A		OBJECT-TYPE
			SYNTAX	INTEGER
			MAX-ACCESS	read-only
			STATUS	current
			::= { hmWanMbus23 91 }

hmWanMbus23VIF2B		OBJECT-TYPE
			SYNTAX	INTEGER
			MAX-ACCESS	read-only
			STATUS	current
			::= { hmWanMbus23 92 }

hmWanMbus23Value2B		OBJECT-TYPE
			SYNTAX	INTEGER
			MAX-ACCESS	read-only
			STATUS	current
			::= { hmWanMbus23 93 }

hmWanMbus23VIF2C		OBJECT-TYPE
			SYNTAX	INTEGER
			MAX-ACCESS	read-only
			STATUS	current
			::= { hmWanMbus23 94 }

hmWanMbus23Value2C		OBJECT-TYPE
			SYNTAX	INTEGER
			MAX-ACCESS	read-only
			STATUS	current
			::= { hmWanMbus23 95 }

hmWanMbus23VIF2D		OBJECT-TYPE
			SYNTAX	INTEGER
			MAX-ACCESS	read-only
			STATUS	current
			::= { hmWanMbus23 96 }

hmWanMbus23Value2D		OBJECT-TYPE
			SYNTAX	INTEGER
			MAX-ACCESS	read-only
			STATUS	current
			::= { hmWanMbus23 97 }

hmWanMbus23VIF2E		OBJECT-TYPE
			SYNTAX	INTEGER
			MAX-ACCESS	read-only
			STATUS	current
			::= { hmWanMbus23 98 }

hmWanMbus23Value2E		OBJECT-TYPE
			SYNTAX	INTEGER
			MAX-ACCESS	read-only
			STATUS	current
			::= { hmWanMbus23 99 }

hmWanMbus23VIF2F		OBJECT-TYPE
			SYNTAX	INTEGER
			MAX-ACCESS	read-only
			STATUS	current
			::= { hmWanMbus23 100 }

hmWanMbus23Value2F		OBJECT-TYPE
			SYNTAX	INTEGER
			MAX-ACCESS	read-only
			STATUS	current
			::= { hmWanMbus23 101 }

hmWanMbus24			OBJECT IDENTIFIER ::= { hmWanMbus 36 }

hmWanMbus24IdNumber		OBJECT-TYPE
			SYNTAX	Gauge32
			MAX-ACCESS	read-only
			STATUS	current
			::= { hmWanMbus24 1 }

hmWanMbus24Manufacturer	OBJECT-TYPE
			SYNTAX	Gauge32
			MAX-ACCESS	read-only
			STATUS	current
			::= { hmWanMbus24 2 }

hmWanMbus24Version		OBJECT-TYPE
			SYNTAX	Gauge32
			MAX-ACCESS	read-only
			STATUS	current
			::= { hmWanMbus24 3 }

hmWanMbus24Medium		OBJECT-TYPE
			SYNTAX	Gauge32
			MAX-ACCESS	read-only
			STATUS	current
			::= { hmWanMbus24 4 }

hmWanMbus24Status		OBJECT-TYPE
			SYNTAX	Gauge32
			MAX-ACCESS	read-only
			STATUS	current
			::= { hmWanMbus24 5 }

hmWanMbus24VIF00		OBJECT-TYPE
			SYNTAX	INTEGER
			MAX-ACCESS	read-only
			STATUS	current
			::= { hmWanMbus24 6 }

hmWanMbus24Value00		OBJECT-TYPE
			SYNTAX	INTEGER
			MAX-ACCESS	read-only
			STATUS	current
			::= { hmWanMbus24 7 }

hmWanMbus24VIF01		OBJECT-TYPE
			SYNTAX	INTEGER
			MAX-ACCESS	read-only
			STATUS	current
			::= { hmWanMbus24 8 }

hmWanMbus24Value01		OBJECT-TYPE
			SYNTAX	INTEGER
			MAX-ACCESS	read-only
			STATUS	current
			::= { hmWanMbus24 9 }

hmWanMbus24VIF02		OBJECT-TYPE
			SYNTAX	INTEGER
			MAX-ACCESS	read-only
			STATUS	current
			::= { hmWanMbus24 10 }

hmWanMbus24Value02		OBJECT-TYPE
			SYNTAX	INTEGER
			MAX-ACCESS	read-only
			STATUS	current
			::= { hmWanMbus24 11 }

hmWanMbus24VIF03		OBJECT-TYPE
			SYNTAX	INTEGER
			MAX-ACCESS	read-only
			STATUS	current
			::= { hmWanMbus24 12 }

hmWanMbus24Value03		OBJECT-TYPE
			SYNTAX	INTEGER
			MAX-ACCESS	read-only
			STATUS	current
			::= { hmWanMbus24 13 }

hmWanMbus24VIF04		OBJECT-TYPE
			SYNTAX	INTEGER
			MAX-ACCESS	read-only
			STATUS	current
			::= { hmWanMbus24 14 }

hmWanMbus24Value04		OBJECT-TYPE
			SYNTAX	INTEGER
			MAX-ACCESS	read-only
			STATUS	current
			::= { hmWanMbus24 15 }

hmWanMbus24VIF05		OBJECT-TYPE
			SYNTAX	INTEGER
			MAX-ACCESS	read-only
			STATUS	current
			::= { hmWanMbus24 16 }

hmWanMbus24Value05		OBJECT-TYPE
			SYNTAX	INTEGER
			MAX-ACCESS	read-only
			STATUS	current
			::= { hmWanMbus24 17 }

hmWanMbus24VIF06		OBJECT-TYPE
			SYNTAX	INTEGER
			MAX-ACCESS	read-only
			STATUS	current
			::= { hmWanMbus24 18 }

hmWanMbus24Value06		OBJECT-TYPE
			SYNTAX	INTEGER
			MAX-ACCESS	read-only
			STATUS	current
			::= { hmWanMbus24 19 }

hmWanMbus24VIF07		OBJECT-TYPE
			SYNTAX	INTEGER
			MAX-ACCESS	read-only
			STATUS	current
			::= { hmWanMbus24 20 }

hmWanMbus24Value07		OBJECT-TYPE
			SYNTAX	INTEGER
			MAX-ACCESS	read-only
			STATUS	current
			::= { hmWanMbus24 21 }

hmWanMbus24VIF08		OBJECT-TYPE
			SYNTAX	INTEGER
			MAX-ACCESS	read-only
			STATUS	current
			::= { hmWanMbus24 22 }

hmWanMbus24Value08		OBJECT-TYPE
			SYNTAX	INTEGER
			MAX-ACCESS	read-only
			STATUS	current
			::= { hmWanMbus24 23 }

hmWanMbus24VIF09		OBJECT-TYPE
			SYNTAX	INTEGER
			MAX-ACCESS	read-only
			STATUS	current
			::= { hmWanMbus24 24 }

hmWanMbus24Value09		OBJECT-TYPE
			SYNTAX	INTEGER
			MAX-ACCESS	read-only
			STATUS	current
			::= { hmWanMbus24 25 }

hmWanMbus24VIF0A		OBJECT-TYPE
			SYNTAX	INTEGER
			MAX-ACCESS	read-only
			STATUS	current
			::= { hmWanMbus24 26 }

hmWanMbus24Value0A		OBJECT-TYPE
			SYNTAX	INTEGER
			MAX-ACCESS	read-only
			STATUS	current
			::= { hmWanMbus24 27 }

hmWanMbus24VIF0B		OBJECT-TYPE
			SYNTAX	INTEGER
			MAX-ACCESS	read-only
			STATUS	current
			::= { hmWanMbus24 28 }

hmWanMbus24Value0B		OBJECT-TYPE
			SYNTAX	INTEGER
			MAX-ACCESS	read-only
			STATUS	current
			::= { hmWanMbus24 29 }

hmWanMbus24VIF0C		OBJECT-TYPE
			SYNTAX	INTEGER
			MAX-ACCESS	read-only
			STATUS	current
			::= { hmWanMbus24 30 }

hmWanMbus24Value0C		OBJECT-TYPE
			SYNTAX	INTEGER
			MAX-ACCESS	read-only
			STATUS	current
			::= { hmWanMbus24 31 }

hmWanMbus24VIF0D		OBJECT-TYPE
			SYNTAX	INTEGER
			MAX-ACCESS	read-only
			STATUS	current
			::= { hmWanMbus24 32 }

hmWanMbus24Value0D		OBJECT-TYPE
			SYNTAX	INTEGER
			MAX-ACCESS	read-only
			STATUS	current
			::= { hmWanMbus24 33 }

hmWanMbus24VIF0E		OBJECT-TYPE
			SYNTAX	INTEGER
			MAX-ACCESS	read-only
			STATUS	current
			::= { hmWanMbus24 34 }

hmWanMbus24Value0E		OBJECT-TYPE
			SYNTAX	INTEGER
			MAX-ACCESS	read-only
			STATUS	current
			::= { hmWanMbus24 35 }

hmWanMbus24VIF0F		OBJECT-TYPE
			SYNTAX	INTEGER
			MAX-ACCESS	read-only
			STATUS	current
			::= { hmWanMbus24 36 }

hmWanMbus24Value0F		OBJECT-TYPE
			SYNTAX	INTEGER
			MAX-ACCESS	read-only
			STATUS	current
			::= { hmWanMbus24 37 }

hmWanMbus24VIF10		OBJECT-TYPE
			SYNTAX	INTEGER
			MAX-ACCESS	read-only
			STATUS	current
			::= { hmWanMbus24 38 }

hmWanMbus24Value10		OBJECT-TYPE
			SYNTAX	INTEGER
			MAX-ACCESS	read-only
			STATUS	current
			::= { hmWanMbus24 39 }

hmWanMbus24VIF11		OBJECT-TYPE
			SYNTAX	INTEGER
			MAX-ACCESS	read-only
			STATUS	current
			::= { hmWanMbus24 40 }

hmWanMbus24Value11		OBJECT-TYPE
			SYNTAX	INTEGER
			MAX-ACCESS	read-only
			STATUS	current
			::= { hmWanMbus24 41 }

hmWanMbus24VIF12		OBJECT-TYPE
			SYNTAX	INTEGER
			MAX-ACCESS	read-only
			STATUS	current
			::= { hmWanMbus24 42 }

hmWanMbus24Value12		OBJECT-TYPE
			SYNTAX	INTEGER
			MAX-ACCESS	read-only
			STATUS	current
			::= { hmWanMbus24 43 }

hmWanMbus24VIF13		OBJECT-TYPE
			SYNTAX	INTEGER
			MAX-ACCESS	read-only
			STATUS	current
			::= { hmWanMbus24 44 }

hmWanMbus24Value13		OBJECT-TYPE
			SYNTAX	INTEGER
			MAX-ACCESS	read-only
			STATUS	current
			::= { hmWanMbus24 45 }

hmWanMbus24VIF14		OBJECT-TYPE
			SYNTAX	INTEGER
			MAX-ACCESS	read-only
			STATUS	current
			::= { hmWanMbus24 46 }

hmWanMbus24Value14		OBJECT-TYPE
			SYNTAX	INTEGER
			MAX-ACCESS	read-only
			STATUS	current
			::= { hmWanMbus24 47 }

hmWanMbus24VIF15		OBJECT-TYPE
			SYNTAX	INTEGER
			MAX-ACCESS	read-only
			STATUS	current
			::= { hmWanMbus24 48 }

hmWanMbus24Value15		OBJECT-TYPE
			SYNTAX	INTEGER
			MAX-ACCESS	read-only
			STATUS	current
			::= { hmWanMbus24 49 }

hmWanMbus24VIF16		OBJECT-TYPE
			SYNTAX	INTEGER
			MAX-ACCESS	read-only
			STATUS	current
			::= { hmWanMbus24 50 }

hmWanMbus24Value16		OBJECT-TYPE
			SYNTAX	INTEGER
			MAX-ACCESS	read-only
			STATUS	current
			::= { hmWanMbus24 51 }

hmWanMbus24VIF17		OBJECT-TYPE
			SYNTAX	INTEGER
			MAX-ACCESS	read-only
			STATUS	current
			::= { hmWanMbus24 52 }

hmWanMbus24Value17		OBJECT-TYPE
			SYNTAX	INTEGER
			MAX-ACCESS	read-only
			STATUS	current
			::= { hmWanMbus24 53 }

hmWanMbus24VIF18		OBJECT-TYPE
			SYNTAX	INTEGER
			MAX-ACCESS	read-only
			STATUS	current
			::= { hmWanMbus24 54 }

hmWanMbus24Value18		OBJECT-TYPE
			SYNTAX	INTEGER
			MAX-ACCESS	read-only
			STATUS	current
			::= { hmWanMbus24 55 }

hmWanMbus24VIF19		OBJECT-TYPE
			SYNTAX	INTEGER
			MAX-ACCESS	read-only
			STATUS	current
			::= { hmWanMbus24 56 }

hmWanMbus24Value19		OBJECT-TYPE
			SYNTAX	INTEGER
			MAX-ACCESS	read-only
			STATUS	current
			::= { hmWanMbus24 57 }

hmWanMbus24VIF1A		OBJECT-TYPE
			SYNTAX	INTEGER
			MAX-ACCESS	read-only
			STATUS	current
			::= { hmWanMbus24 58 }

hmWanMbus24Value1A		OBJECT-TYPE
			SYNTAX	INTEGER
			MAX-ACCESS	read-only
			STATUS	current
			::= { hmWanMbus24 59 }

hmWanMbus24VIF1B		OBJECT-TYPE
			SYNTAX	INTEGER
			MAX-ACCESS	read-only
			STATUS	current
			::= { hmWanMbus24 60 }

hmWanMbus24Value1B		OBJECT-TYPE
			SYNTAX	INTEGER
			MAX-ACCESS	read-only
			STATUS	current
			::= { hmWanMbus24 61 }

hmWanMbus24VIF1C		OBJECT-TYPE
			SYNTAX	INTEGER
			MAX-ACCESS	read-only
			STATUS	current
			::= { hmWanMbus24 62 }

hmWanMbus24Value1C		OBJECT-TYPE
			SYNTAX	INTEGER
			MAX-ACCESS	read-only
			STATUS	current
			::= { hmWanMbus24 63 }

hmWanMbus24VIF1D		OBJECT-TYPE
			SYNTAX	INTEGER
			MAX-ACCESS	read-only
			STATUS	current
			::= { hmWanMbus24 64 }

hmWanMbus24Value1D		OBJECT-TYPE
			SYNTAX	INTEGER
			MAX-ACCESS	read-only
			STATUS	current
			::= { hmWanMbus24 65 }

hmWanMbus24VIF1E		OBJECT-TYPE
			SYNTAX	INTEGER
			MAX-ACCESS	read-only
			STATUS	current
			::= { hmWanMbus24 66 }

hmWanMbus24Value1E		OBJECT-TYPE
			SYNTAX	INTEGER
			MAX-ACCESS	read-only
			STATUS	current
			::= { hmWanMbus24 67 }

hmWanMbus24VIF1F		OBJECT-TYPE
			SYNTAX	INTEGER
			MAX-ACCESS	read-only
			STATUS	current
			::= { hmWanMbus24 68 }

hmWanMbus24Value1F		OBJECT-TYPE
			SYNTAX	INTEGER
			MAX-ACCESS	read-only
			STATUS	current
			::= { hmWanMbus24 69 }

hmWanMbus24VIF20		OBJECT-TYPE
			SYNTAX	INTEGER
			MAX-ACCESS	read-only
			STATUS	current
			::= { hmWanMbus24 70 }

hmWanMbus24Value20		OBJECT-TYPE
			SYNTAX	INTEGER
			MAX-ACCESS	read-only
			STATUS	current
			::= { hmWanMbus24 71 }

hmWanMbus24VIF21		OBJECT-TYPE
			SYNTAX	INTEGER
			MAX-ACCESS	read-only
			STATUS	current
			::= { hmWanMbus24 72 }

hmWanMbus24Value21		OBJECT-TYPE
			SYNTAX	INTEGER
			MAX-ACCESS	read-only
			STATUS	current
			::= { hmWanMbus24 73 }

hmWanMbus24VIF22		OBJECT-TYPE
			SYNTAX	INTEGER
			MAX-ACCESS	read-only
			STATUS	current
			::= { hmWanMbus24 74 }

hmWanMbus24Value22		OBJECT-TYPE
			SYNTAX	INTEGER
			MAX-ACCESS	read-only
			STATUS	current
			::= { hmWanMbus24 75 }

hmWanMbus24VIF23		OBJECT-TYPE
			SYNTAX	INTEGER
			MAX-ACCESS	read-only
			STATUS	current
			::= { hmWanMbus24 76 }

hmWanMbus24Value23		OBJECT-TYPE
			SYNTAX	INTEGER
			MAX-ACCESS	read-only
			STATUS	current
			::= { hmWanMbus24 77 }

hmWanMbus24VIF24		OBJECT-TYPE
			SYNTAX	INTEGER
			MAX-ACCESS	read-only
			STATUS	current
			::= { hmWanMbus24 78 }

hmWanMbus24Value24		OBJECT-TYPE
			SYNTAX	INTEGER
			MAX-ACCESS	read-only
			STATUS	current
			::= { hmWanMbus24 79 }

hmWanMbus24VIF25		OBJECT-TYPE
			SYNTAX	INTEGER
			MAX-ACCESS	read-only
			STATUS	current
			::= { hmWanMbus24 80 }

hmWanMbus24Value25		OBJECT-TYPE
			SYNTAX	INTEGER
			MAX-ACCESS	read-only
			STATUS	current
			::= { hmWanMbus24 81 }

hmWanMbus24VIF26		OBJECT-TYPE
			SYNTAX	INTEGER
			MAX-ACCESS	read-only
			STATUS	current
			::= { hmWanMbus24 82 }

hmWanMbus24Value26		OBJECT-TYPE
			SYNTAX	INTEGER
			MAX-ACCESS	read-only
			STATUS	current
			::= { hmWanMbus24 83 }

hmWanMbus24VIF27		OBJECT-TYPE
			SYNTAX	INTEGER
			MAX-ACCESS	read-only
			STATUS	current
			::= { hmWanMbus24 84 }

hmWanMbus24Value27		OBJECT-TYPE
			SYNTAX	INTEGER
			MAX-ACCESS	read-only
			STATUS	current
			::= { hmWanMbus24 85 }

hmWanMbus24VIF28		OBJECT-TYPE
			SYNTAX	INTEGER
			MAX-ACCESS	read-only
			STATUS	current
			::= { hmWanMbus24 86 }

hmWanMbus24Value28		OBJECT-TYPE
			SYNTAX	INTEGER
			MAX-ACCESS	read-only
			STATUS	current
			::= { hmWanMbus24 87 }

hmWanMbus24VIF29		OBJECT-TYPE
			SYNTAX	INTEGER
			MAX-ACCESS	read-only
			STATUS	current
			::= { hmWanMbus24 88 }

hmWanMbus24Value29		OBJECT-TYPE
			SYNTAX	INTEGER
			MAX-ACCESS	read-only
			STATUS	current
			::= { hmWanMbus24 89 }

hmWanMbus24VIF2A		OBJECT-TYPE
			SYNTAX	INTEGER
			MAX-ACCESS	read-only
			STATUS	current
			::= { hmWanMbus24 90 }

hmWanMbus24Value2A		OBJECT-TYPE
			SYNTAX	INTEGER
			MAX-ACCESS	read-only
			STATUS	current
			::= { hmWanMbus24 91 }

hmWanMbus24VIF2B		OBJECT-TYPE
			SYNTAX	INTEGER
			MAX-ACCESS	read-only
			STATUS	current
			::= { hmWanMbus24 92 }

hmWanMbus24Value2B		OBJECT-TYPE
			SYNTAX	INTEGER
			MAX-ACCESS	read-only
			STATUS	current
			::= { hmWanMbus24 93 }

hmWanMbus24VIF2C		OBJECT-TYPE
			SYNTAX	INTEGER
			MAX-ACCESS	read-only
			STATUS	current
			::= { hmWanMbus24 94 }

hmWanMbus24Value2C		OBJECT-TYPE
			SYNTAX	INTEGER
			MAX-ACCESS	read-only
			STATUS	current
			::= { hmWanMbus24 95 }

hmWanMbus24VIF2D		OBJECT-TYPE
			SYNTAX	INTEGER
			MAX-ACCESS	read-only
			STATUS	current
			::= { hmWanMbus24 96 }

hmWanMbus24Value2D		OBJECT-TYPE
			SYNTAX	INTEGER
			MAX-ACCESS	read-only
			STATUS	current
			::= { hmWanMbus24 97 }

hmWanMbus24VIF2E		OBJECT-TYPE
			SYNTAX	INTEGER
			MAX-ACCESS	read-only
			STATUS	current
			::= { hmWanMbus24 98 }

hmWanMbus24Value2E		OBJECT-TYPE
			SYNTAX	INTEGER
			MAX-ACCESS	read-only
			STATUS	current
			::= { hmWanMbus24 99 }

hmWanMbus24VIF2F		OBJECT-TYPE
			SYNTAX	INTEGER
			MAX-ACCESS	read-only
			STATUS	current
			::= { hmWanMbus24 100 }

hmWanMbus24Value2F		OBJECT-TYPE
			SYNTAX	INTEGER
			MAX-ACCESS	read-only
			STATUS	current
			::= { hmWanMbus24 101 }

hmWanMbus25			OBJECT IDENTIFIER ::= { hmWanMbus 37 }

hmWanMbus25IdNumber		OBJECT-TYPE
			SYNTAX	Gauge32
			MAX-ACCESS	read-only
			STATUS	current
			::= { hmWanMbus25 1 }

hmWanMbus25Manufacturer	OBJECT-TYPE
			SYNTAX	Gauge32
			MAX-ACCESS	read-only
			STATUS	current
			::= { hmWanMbus25 2 }

hmWanMbus25Version		OBJECT-TYPE
			SYNTAX	Gauge32
			MAX-ACCESS	read-only
			STATUS	current
			::= { hmWanMbus25 3 }

hmWanMbus25Medium		OBJECT-TYPE
			SYNTAX	Gauge32
			MAX-ACCESS	read-only
			STATUS	current
			::= { hmWanMbus25 4 }

hmWanMbus25Status		OBJECT-TYPE
			SYNTAX	Gauge32
			MAX-ACCESS	read-only
			STATUS	current
			::= { hmWanMbus25 5 }

hmWanMbus25VIF00		OBJECT-TYPE
			SYNTAX	INTEGER
			MAX-ACCESS	read-only
			STATUS	current
			::= { hmWanMbus25 6 }

hmWanMbus25Value00		OBJECT-TYPE
			SYNTAX	INTEGER
			MAX-ACCESS	read-only
			STATUS	current
			::= { hmWanMbus25 7 }

hmWanMbus25VIF01		OBJECT-TYPE
			SYNTAX	INTEGER
			MAX-ACCESS	read-only
			STATUS	current
			::= { hmWanMbus25 8 }

hmWanMbus25Value01		OBJECT-TYPE
			SYNTAX	INTEGER
			MAX-ACCESS	read-only
			STATUS	current
			::= { hmWanMbus25 9 }

hmWanMbus25VIF02		OBJECT-TYPE
			SYNTAX	INTEGER
			MAX-ACCESS	read-only
			STATUS	current
			::= { hmWanMbus25 10 }

hmWanMbus25Value02		OBJECT-TYPE
			SYNTAX	INTEGER
			MAX-ACCESS	read-only
			STATUS	current
			::= { hmWanMbus25 11 }

hmWanMbus25VIF03		OBJECT-TYPE
			SYNTAX	INTEGER
			MAX-ACCESS	read-only
			STATUS	current
			::= { hmWanMbus25 12 }

hmWanMbus25Value03		OBJECT-TYPE
			SYNTAX	INTEGER
			MAX-ACCESS	read-only
			STATUS	current
			::= { hmWanMbus25 13 }

hmWanMbus25VIF04		OBJECT-TYPE
			SYNTAX	INTEGER
			MAX-ACCESS	read-only
			STATUS	current
			::= { hmWanMbus25 14 }

hmWanMbus25Value04		OBJECT-TYPE
			SYNTAX	INTEGER
			MAX-ACCESS	read-only
			STATUS	current
			::= { hmWanMbus25 15 }

hmWanMbus25VIF05		OBJECT-TYPE
			SYNTAX	INTEGER
			MAX-ACCESS	read-only
			STATUS	current
			::= { hmWanMbus25 16 }

hmWanMbus25Value05		OBJECT-TYPE
			SYNTAX	INTEGER
			MAX-ACCESS	read-only
			STATUS	current
			::= { hmWanMbus25 17 }

hmWanMbus25VIF06		OBJECT-TYPE
			SYNTAX	INTEGER
			MAX-ACCESS	read-only
			STATUS	current
			::= { hmWanMbus25 18 }

hmWanMbus25Value06		OBJECT-TYPE
			SYNTAX	INTEGER
			MAX-ACCESS	read-only
			STATUS	current
			::= { hmWanMbus25 19 }

hmWanMbus25VIF07		OBJECT-TYPE
			SYNTAX	INTEGER
			MAX-ACCESS	read-only
			STATUS	current
			::= { hmWanMbus25 20 }

hmWanMbus25Value07		OBJECT-TYPE
			SYNTAX	INTEGER
			MAX-ACCESS	read-only
			STATUS	current
			::= { hmWanMbus25 21 }

hmWanMbus25VIF08		OBJECT-TYPE
			SYNTAX	INTEGER
			MAX-ACCESS	read-only
			STATUS	current
			::= { hmWanMbus25 22 }

hmWanMbus25Value08		OBJECT-TYPE
			SYNTAX	INTEGER
			MAX-ACCESS	read-only
			STATUS	current
			::= { hmWanMbus25 23 }

hmWanMbus25VIF09		OBJECT-TYPE
			SYNTAX	INTEGER
			MAX-ACCESS	read-only
			STATUS	current
			::= { hmWanMbus25 24 }

hmWanMbus25Value09		OBJECT-TYPE
			SYNTAX	INTEGER
			MAX-ACCESS	read-only
			STATUS	current
			::= { hmWanMbus25 25 }

hmWanMbus25VIF0A		OBJECT-TYPE
			SYNTAX	INTEGER
			MAX-ACCESS	read-only
			STATUS	current
			::= { hmWanMbus25 26 }

hmWanMbus25Value0A		OBJECT-TYPE
			SYNTAX	INTEGER
			MAX-ACCESS	read-only
			STATUS	current
			::= { hmWanMbus25 27 }

hmWanMbus25VIF0B		OBJECT-TYPE
			SYNTAX	INTEGER
			MAX-ACCESS	read-only
			STATUS	current
			::= { hmWanMbus25 28 }

hmWanMbus25Value0B		OBJECT-TYPE
			SYNTAX	INTEGER
			MAX-ACCESS	read-only
			STATUS	current
			::= { hmWanMbus25 29 }

hmWanMbus25VIF0C		OBJECT-TYPE
			SYNTAX	INTEGER
			MAX-ACCESS	read-only
			STATUS	current
			::= { hmWanMbus25 30 }

hmWanMbus25Value0C		OBJECT-TYPE
			SYNTAX	INTEGER
			MAX-ACCESS	read-only
			STATUS	current
			::= { hmWanMbus25 31 }

hmWanMbus25VIF0D		OBJECT-TYPE
			SYNTAX	INTEGER
			MAX-ACCESS	read-only
			STATUS	current
			::= { hmWanMbus25 32 }

hmWanMbus25Value0D		OBJECT-TYPE
			SYNTAX	INTEGER
			MAX-ACCESS	read-only
			STATUS	current
			::= { hmWanMbus25 33 }

hmWanMbus25VIF0E		OBJECT-TYPE
			SYNTAX	INTEGER
			MAX-ACCESS	read-only
			STATUS	current
			::= { hmWanMbus25 34 }

hmWanMbus25Value0E		OBJECT-TYPE
			SYNTAX	INTEGER
			MAX-ACCESS	read-only
			STATUS	current
			::= { hmWanMbus25 35 }

hmWanMbus25VIF0F		OBJECT-TYPE
			SYNTAX	INTEGER
			MAX-ACCESS	read-only
			STATUS	current
			::= { hmWanMbus25 36 }

hmWanMbus25Value0F		OBJECT-TYPE
			SYNTAX	INTEGER
			MAX-ACCESS	read-only
			STATUS	current
			::= { hmWanMbus25 37 }

hmWanMbus25VIF10		OBJECT-TYPE
			SYNTAX	INTEGER
			MAX-ACCESS	read-only
			STATUS	current
			::= { hmWanMbus25 38 }

hmWanMbus25Value10		OBJECT-TYPE
			SYNTAX	INTEGER
			MAX-ACCESS	read-only
			STATUS	current
			::= { hmWanMbus25 39 }

hmWanMbus25VIF11		OBJECT-TYPE
			SYNTAX	INTEGER
			MAX-ACCESS	read-only
			STATUS	current
			::= { hmWanMbus25 40 }

hmWanMbus25Value11		OBJECT-TYPE
			SYNTAX	INTEGER
			MAX-ACCESS	read-only
			STATUS	current
			::= { hmWanMbus25 41 }

hmWanMbus25VIF12		OBJECT-TYPE
			SYNTAX	INTEGER
			MAX-ACCESS	read-only
			STATUS	current
			::= { hmWanMbus25 42 }

hmWanMbus25Value12		OBJECT-TYPE
			SYNTAX	INTEGER
			MAX-ACCESS	read-only
			STATUS	current
			::= { hmWanMbus25 43 }

hmWanMbus25VIF13		OBJECT-TYPE
			SYNTAX	INTEGER
			MAX-ACCESS	read-only
			STATUS	current
			::= { hmWanMbus25 44 }

hmWanMbus25Value13		OBJECT-TYPE
			SYNTAX	INTEGER
			MAX-ACCESS	read-only
			STATUS	current
			::= { hmWanMbus25 45 }

hmWanMbus25VIF14		OBJECT-TYPE
			SYNTAX	INTEGER
			MAX-ACCESS	read-only
			STATUS	current
			::= { hmWanMbus25 46 }

hmWanMbus25Value14		OBJECT-TYPE
			SYNTAX	INTEGER
			MAX-ACCESS	read-only
			STATUS	current
			::= { hmWanMbus25 47 }

hmWanMbus25VIF15		OBJECT-TYPE
			SYNTAX	INTEGER
			MAX-ACCESS	read-only
			STATUS	current
			::= { hmWanMbus25 48 }

hmWanMbus25Value15		OBJECT-TYPE
			SYNTAX	INTEGER
			MAX-ACCESS	read-only
			STATUS	current
			::= { hmWanMbus25 49 }

hmWanMbus25VIF16		OBJECT-TYPE
			SYNTAX	INTEGER
			MAX-ACCESS	read-only
			STATUS	current
			::= { hmWanMbus25 50 }

hmWanMbus25Value16		OBJECT-TYPE
			SYNTAX	INTEGER
			MAX-ACCESS	read-only
			STATUS	current
			::= { hmWanMbus25 51 }

hmWanMbus25VIF17		OBJECT-TYPE
			SYNTAX	INTEGER
			MAX-ACCESS	read-only
			STATUS	current
			::= { hmWanMbus25 52 }

hmWanMbus25Value17		OBJECT-TYPE
			SYNTAX	INTEGER
			MAX-ACCESS	read-only
			STATUS	current
			::= { hmWanMbus25 53 }

hmWanMbus25VIF18		OBJECT-TYPE
			SYNTAX	INTEGER
			MAX-ACCESS	read-only
			STATUS	current
			::= { hmWanMbus25 54 }

hmWanMbus25Value18		OBJECT-TYPE
			SYNTAX	INTEGER
			MAX-ACCESS	read-only
			STATUS	current
			::= { hmWanMbus25 55 }

hmWanMbus25VIF19		OBJECT-TYPE
			SYNTAX	INTEGER
			MAX-ACCESS	read-only
			STATUS	current
			::= { hmWanMbus25 56 }

hmWanMbus25Value19		OBJECT-TYPE
			SYNTAX	INTEGER
			MAX-ACCESS	read-only
			STATUS	current
			::= { hmWanMbus25 57 }

hmWanMbus25VIF1A		OBJECT-TYPE
			SYNTAX	INTEGER
			MAX-ACCESS	read-only
			STATUS	current
			::= { hmWanMbus25 58 }

hmWanMbus25Value1A		OBJECT-TYPE
			SYNTAX	INTEGER
			MAX-ACCESS	read-only
			STATUS	current
			::= { hmWanMbus25 59 }

hmWanMbus25VIF1B		OBJECT-TYPE
			SYNTAX	INTEGER
			MAX-ACCESS	read-only
			STATUS	current
			::= { hmWanMbus25 60 }

hmWanMbus25Value1B		OBJECT-TYPE
			SYNTAX	INTEGER
			MAX-ACCESS	read-only
			STATUS	current
			::= { hmWanMbus25 61 }

hmWanMbus25VIF1C		OBJECT-TYPE
			SYNTAX	INTEGER
			MAX-ACCESS	read-only
			STATUS	current
			::= { hmWanMbus25 62 }

hmWanMbus25Value1C		OBJECT-TYPE
			SYNTAX	INTEGER
			MAX-ACCESS	read-only
			STATUS	current
			::= { hmWanMbus25 63 }

hmWanMbus25VIF1D		OBJECT-TYPE
			SYNTAX	INTEGER
			MAX-ACCESS	read-only
			STATUS	current
			::= { hmWanMbus25 64 }

hmWanMbus25Value1D		OBJECT-TYPE
			SYNTAX	INTEGER
			MAX-ACCESS	read-only
			STATUS	current
			::= { hmWanMbus25 65 }

hmWanMbus25VIF1E		OBJECT-TYPE
			SYNTAX	INTEGER
			MAX-ACCESS	read-only
			STATUS	current
			::= { hmWanMbus25 66 }

hmWanMbus25Value1E		OBJECT-TYPE
			SYNTAX	INTEGER
			MAX-ACCESS	read-only
			STATUS	current
			::= { hmWanMbus25 67 }

hmWanMbus25VIF1F		OBJECT-TYPE
			SYNTAX	INTEGER
			MAX-ACCESS	read-only
			STATUS	current
			::= { hmWanMbus25 68 }

hmWanMbus25Value1F		OBJECT-TYPE
			SYNTAX	INTEGER
			MAX-ACCESS	read-only
			STATUS	current
			::= { hmWanMbus25 69 }

hmWanMbus25VIF20		OBJECT-TYPE
			SYNTAX	INTEGER
			MAX-ACCESS	read-only
			STATUS	current
			::= { hmWanMbus25 70 }

hmWanMbus25Value20		OBJECT-TYPE
			SYNTAX	INTEGER
			MAX-ACCESS	read-only
			STATUS	current
			::= { hmWanMbus25 71 }

hmWanMbus25VIF21		OBJECT-TYPE
			SYNTAX	INTEGER
			MAX-ACCESS	read-only
			STATUS	current
			::= { hmWanMbus25 72 }

hmWanMbus25Value21		OBJECT-TYPE
			SYNTAX	INTEGER
			MAX-ACCESS	read-only
			STATUS	current
			::= { hmWanMbus25 73 }

hmWanMbus25VIF22		OBJECT-TYPE
			SYNTAX	INTEGER
			MAX-ACCESS	read-only
			STATUS	current
			::= { hmWanMbus25 74 }

hmWanMbus25Value22		OBJECT-TYPE
			SYNTAX	INTEGER
			MAX-ACCESS	read-only
			STATUS	current
			::= { hmWanMbus25 75 }

hmWanMbus25VIF23		OBJECT-TYPE
			SYNTAX	INTEGER
			MAX-ACCESS	read-only
			STATUS	current
			::= { hmWanMbus25 76 }

hmWanMbus25Value23		OBJECT-TYPE
			SYNTAX	INTEGER
			MAX-ACCESS	read-only
			STATUS	current
			::= { hmWanMbus25 77 }

hmWanMbus25VIF24		OBJECT-TYPE
			SYNTAX	INTEGER
			MAX-ACCESS	read-only
			STATUS	current
			::= { hmWanMbus25 78 }

hmWanMbus25Value24		OBJECT-TYPE
			SYNTAX	INTEGER
			MAX-ACCESS	read-only
			STATUS	current
			::= { hmWanMbus25 79 }

hmWanMbus25VIF25		OBJECT-TYPE
			SYNTAX	INTEGER
			MAX-ACCESS	read-only
			STATUS	current
			::= { hmWanMbus25 80 }

hmWanMbus25Value25		OBJECT-TYPE
			SYNTAX	INTEGER
			MAX-ACCESS	read-only
			STATUS	current
			::= { hmWanMbus25 81 }

hmWanMbus25VIF26		OBJECT-TYPE
			SYNTAX	INTEGER
			MAX-ACCESS	read-only
			STATUS	current
			::= { hmWanMbus25 82 }

hmWanMbus25Value26		OBJECT-TYPE
			SYNTAX	INTEGER
			MAX-ACCESS	read-only
			STATUS	current
			::= { hmWanMbus25 83 }

hmWanMbus25VIF27		OBJECT-TYPE
			SYNTAX	INTEGER
			MAX-ACCESS	read-only
			STATUS	current
			::= { hmWanMbus25 84 }

hmWanMbus25Value27		OBJECT-TYPE
			SYNTAX	INTEGER
			MAX-ACCESS	read-only
			STATUS	current
			::= { hmWanMbus25 85 }

hmWanMbus25VIF28		OBJECT-TYPE
			SYNTAX	INTEGER
			MAX-ACCESS	read-only
			STATUS	current
			::= { hmWanMbus25 86 }

hmWanMbus25Value28		OBJECT-TYPE
			SYNTAX	INTEGER
			MAX-ACCESS	read-only
			STATUS	current
			::= { hmWanMbus25 87 }

hmWanMbus25VIF29		OBJECT-TYPE
			SYNTAX	INTEGER
			MAX-ACCESS	read-only
			STATUS	current
			::= { hmWanMbus25 88 }

hmWanMbus25Value29		OBJECT-TYPE
			SYNTAX	INTEGER
			MAX-ACCESS	read-only
			STATUS	current
			::= { hmWanMbus25 89 }

hmWanMbus25VIF2A		OBJECT-TYPE
			SYNTAX	INTEGER
			MAX-ACCESS	read-only
			STATUS	current
			::= { hmWanMbus25 90 }

hmWanMbus25Value2A		OBJECT-TYPE
			SYNTAX	INTEGER
			MAX-ACCESS	read-only
			STATUS	current
			::= { hmWanMbus25 91 }

hmWanMbus25VIF2B		OBJECT-TYPE
			SYNTAX	INTEGER
			MAX-ACCESS	read-only
			STATUS	current
			::= { hmWanMbus25 92 }

hmWanMbus25Value2B		OBJECT-TYPE
			SYNTAX	INTEGER
			MAX-ACCESS	read-only
			STATUS	current
			::= { hmWanMbus25 93 }

hmWanMbus25VIF2C		OBJECT-TYPE
			SYNTAX	INTEGER
			MAX-ACCESS	read-only
			STATUS	current
			::= { hmWanMbus25 94 }

hmWanMbus25Value2C		OBJECT-TYPE
			SYNTAX	INTEGER
			MAX-ACCESS	read-only
			STATUS	current
			::= { hmWanMbus25 95 }

hmWanMbus25VIF2D		OBJECT-TYPE
			SYNTAX	INTEGER
			MAX-ACCESS	read-only
			STATUS	current
			::= { hmWanMbus25 96 }

hmWanMbus25Value2D		OBJECT-TYPE
			SYNTAX	INTEGER
			MAX-ACCESS	read-only
			STATUS	current
			::= { hmWanMbus25 97 }

hmWanMbus25VIF2E		OBJECT-TYPE
			SYNTAX	INTEGER
			MAX-ACCESS	read-only
			STATUS	current
			::= { hmWanMbus25 98 }

hmWanMbus25Value2E		OBJECT-TYPE
			SYNTAX	INTEGER
			MAX-ACCESS	read-only
			STATUS	current
			::= { hmWanMbus25 99 }

hmWanMbus25VIF2F		OBJECT-TYPE
			SYNTAX	INTEGER
			MAX-ACCESS	read-only
			STATUS	current
			::= { hmWanMbus25 100 }

hmWanMbus25Value2F		OBJECT-TYPE
			SYNTAX	INTEGER
			MAX-ACCESS	read-only
			STATUS	current
			::= { hmWanMbus25 101 }

hmWanMbus26			OBJECT IDENTIFIER ::= { hmWanMbus 38 }

hmWanMbus26IdNumber		OBJECT-TYPE
			SYNTAX	Gauge32
			MAX-ACCESS	read-only
			STATUS	current
			::= { hmWanMbus26 1 }

hmWanMbus26Manufacturer	OBJECT-TYPE
			SYNTAX	Gauge32
			MAX-ACCESS	read-only
			STATUS	current
			::= { hmWanMbus26 2 }

hmWanMbus26Version		OBJECT-TYPE
			SYNTAX	Gauge32
			MAX-ACCESS	read-only
			STATUS	current
			::= { hmWanMbus26 3 }

hmWanMbus26Medium		OBJECT-TYPE
			SYNTAX	Gauge32
			MAX-ACCESS	read-only
			STATUS	current
			::= { hmWanMbus26 4 }

hmWanMbus26Status		OBJECT-TYPE
			SYNTAX	Gauge32
			MAX-ACCESS	read-only
			STATUS	current
			::= { hmWanMbus26 5 }

hmWanMbus26VIF00		OBJECT-TYPE
			SYNTAX	INTEGER
			MAX-ACCESS	read-only
			STATUS	current
			::= { hmWanMbus26 6 }

hmWanMbus26Value00		OBJECT-TYPE
			SYNTAX	INTEGER
			MAX-ACCESS	read-only
			STATUS	current
			::= { hmWanMbus26 7 }

hmWanMbus26VIF01		OBJECT-TYPE
			SYNTAX	INTEGER
			MAX-ACCESS	read-only
			STATUS	current
			::= { hmWanMbus26 8 }

hmWanMbus26Value01		OBJECT-TYPE
			SYNTAX	INTEGER
			MAX-ACCESS	read-only
			STATUS	current
			::= { hmWanMbus26 9 }

hmWanMbus26VIF02		OBJECT-TYPE
			SYNTAX	INTEGER
			MAX-ACCESS	read-only
			STATUS	current
			::= { hmWanMbus26 10 }

hmWanMbus26Value02		OBJECT-TYPE
			SYNTAX	INTEGER
			MAX-ACCESS	read-only
			STATUS	current
			::= { hmWanMbus26 11 }

hmWanMbus26VIF03		OBJECT-TYPE
			SYNTAX	INTEGER
			MAX-ACCESS	read-only
			STATUS	current
			::= { hmWanMbus26 12 }

hmWanMbus26Value03		OBJECT-TYPE
			SYNTAX	INTEGER
			MAX-ACCESS	read-only
			STATUS	current
			::= { hmWanMbus26 13 }

hmWanMbus26VIF04		OBJECT-TYPE
			SYNTAX	INTEGER
			MAX-ACCESS	read-only
			STATUS	current
			::= { hmWanMbus26 14 }

hmWanMbus26Value04		OBJECT-TYPE
			SYNTAX	INTEGER
			MAX-ACCESS	read-only
			STATUS	current
			::= { hmWanMbus26 15 }

hmWanMbus26VIF05		OBJECT-TYPE
			SYNTAX	INTEGER
			MAX-ACCESS	read-only
			STATUS	current
			::= { hmWanMbus26 16 }

hmWanMbus26Value05		OBJECT-TYPE
			SYNTAX	INTEGER
			MAX-ACCESS	read-only
			STATUS	current
			::= { hmWanMbus26 17 }

hmWanMbus26VIF06		OBJECT-TYPE
			SYNTAX	INTEGER
			MAX-ACCESS	read-only
			STATUS	current
			::= { hmWanMbus26 18 }

hmWanMbus26Value06		OBJECT-TYPE
			SYNTAX	INTEGER
			MAX-ACCESS	read-only
			STATUS	current
			::= { hmWanMbus26 19 }

hmWanMbus26VIF07		OBJECT-TYPE
			SYNTAX	INTEGER
			MAX-ACCESS	read-only
			STATUS	current
			::= { hmWanMbus26 20 }

hmWanMbus26Value07		OBJECT-TYPE
			SYNTAX	INTEGER
			MAX-ACCESS	read-only
			STATUS	current
			::= { hmWanMbus26 21 }

hmWanMbus26VIF08		OBJECT-TYPE
			SYNTAX	INTEGER
			MAX-ACCESS	read-only
			STATUS	current
			::= { hmWanMbus26 22 }

hmWanMbus26Value08		OBJECT-TYPE
			SYNTAX	INTEGER
			MAX-ACCESS	read-only
			STATUS	current
			::= { hmWanMbus26 23 }

hmWanMbus26VIF09		OBJECT-TYPE
			SYNTAX	INTEGER
			MAX-ACCESS	read-only
			STATUS	current
			::= { hmWanMbus26 24 }

hmWanMbus26Value09		OBJECT-TYPE
			SYNTAX	INTEGER
			MAX-ACCESS	read-only
			STATUS	current
			::= { hmWanMbus26 25 }

hmWanMbus26VIF0A		OBJECT-TYPE
			SYNTAX	INTEGER
			MAX-ACCESS	read-only
			STATUS	current
			::= { hmWanMbus26 26 }

hmWanMbus26Value0A		OBJECT-TYPE
			SYNTAX	INTEGER
			MAX-ACCESS	read-only
			STATUS	current
			::= { hmWanMbus26 27 }

hmWanMbus26VIF0B		OBJECT-TYPE
			SYNTAX	INTEGER
			MAX-ACCESS	read-only
			STATUS	current
			::= { hmWanMbus26 28 }

hmWanMbus26Value0B		OBJECT-TYPE
			SYNTAX	INTEGER
			MAX-ACCESS	read-only
			STATUS	current
			::= { hmWanMbus26 29 }

hmWanMbus26VIF0C		OBJECT-TYPE
			SYNTAX	INTEGER
			MAX-ACCESS	read-only
			STATUS	current
			::= { hmWanMbus26 30 }

hmWanMbus26Value0C		OBJECT-TYPE
			SYNTAX	INTEGER
			MAX-ACCESS	read-only
			STATUS	current
			::= { hmWanMbus26 31 }

hmWanMbus26VIF0D		OBJECT-TYPE
			SYNTAX	INTEGER
			MAX-ACCESS	read-only
			STATUS	current
			::= { hmWanMbus26 32 }

hmWanMbus26Value0D		OBJECT-TYPE
			SYNTAX	INTEGER
			MAX-ACCESS	read-only
			STATUS	current
			::= { hmWanMbus26 33 }

hmWanMbus26VIF0E		OBJECT-TYPE
			SYNTAX	INTEGER
			MAX-ACCESS	read-only
			STATUS	current
			::= { hmWanMbus26 34 }

hmWanMbus26Value0E		OBJECT-TYPE
			SYNTAX	INTEGER
			MAX-ACCESS	read-only
			STATUS	current
			::= { hmWanMbus26 35 }

hmWanMbus26VIF0F		OBJECT-TYPE
			SYNTAX	INTEGER
			MAX-ACCESS	read-only
			STATUS	current
			::= { hmWanMbus26 36 }

hmWanMbus26Value0F		OBJECT-TYPE
			SYNTAX	INTEGER
			MAX-ACCESS	read-only
			STATUS	current
			::= { hmWanMbus26 37 }

hmWanMbus26VIF10		OBJECT-TYPE
			SYNTAX	INTEGER
			MAX-ACCESS	read-only
			STATUS	current
			::= { hmWanMbus26 38 }

hmWanMbus26Value10		OBJECT-TYPE
			SYNTAX	INTEGER
			MAX-ACCESS	read-only
			STATUS	current
			::= { hmWanMbus26 39 }

hmWanMbus26VIF11		OBJECT-TYPE
			SYNTAX	INTEGER
			MAX-ACCESS	read-only
			STATUS	current
			::= { hmWanMbus26 40 }

hmWanMbus26Value11		OBJECT-TYPE
			SYNTAX	INTEGER
			MAX-ACCESS	read-only
			STATUS	current
			::= { hmWanMbus26 41 }

hmWanMbus26VIF12		OBJECT-TYPE
			SYNTAX	INTEGER
			MAX-ACCESS	read-only
			STATUS	current
			::= { hmWanMbus26 42 }

hmWanMbus26Value12		OBJECT-TYPE
			SYNTAX	INTEGER
			MAX-ACCESS	read-only
			STATUS	current
			::= { hmWanMbus26 43 }

hmWanMbus26VIF13		OBJECT-TYPE
			SYNTAX	INTEGER
			MAX-ACCESS	read-only
			STATUS	current
			::= { hmWanMbus26 44 }

hmWanMbus26Value13		OBJECT-TYPE
			SYNTAX	INTEGER
			MAX-ACCESS	read-only
			STATUS	current
			::= { hmWanMbus26 45 }

hmWanMbus26VIF14		OBJECT-TYPE
			SYNTAX	INTEGER
			MAX-ACCESS	read-only
			STATUS	current
			::= { hmWanMbus26 46 }

hmWanMbus26Value14		OBJECT-TYPE
			SYNTAX	INTEGER
			MAX-ACCESS	read-only
			STATUS	current
			::= { hmWanMbus26 47 }

hmWanMbus26VIF15		OBJECT-TYPE
			SYNTAX	INTEGER
			MAX-ACCESS	read-only
			STATUS	current
			::= { hmWanMbus26 48 }

hmWanMbus26Value15		OBJECT-TYPE
			SYNTAX	INTEGER
			MAX-ACCESS	read-only
			STATUS	current
			::= { hmWanMbus26 49 }

hmWanMbus26VIF16		OBJECT-TYPE
			SYNTAX	INTEGER
			MAX-ACCESS	read-only
			STATUS	current
			::= { hmWanMbus26 50 }

hmWanMbus26Value16		OBJECT-TYPE
			SYNTAX	INTEGER
			MAX-ACCESS	read-only
			STATUS	current
			::= { hmWanMbus26 51 }

hmWanMbus26VIF17		OBJECT-TYPE
			SYNTAX	INTEGER
			MAX-ACCESS	read-only
			STATUS	current
			::= { hmWanMbus26 52 }

hmWanMbus26Value17		OBJECT-TYPE
			SYNTAX	INTEGER
			MAX-ACCESS	read-only
			STATUS	current
			::= { hmWanMbus26 53 }

hmWanMbus26VIF18		OBJECT-TYPE
			SYNTAX	INTEGER
			MAX-ACCESS	read-only
			STATUS	current
			::= { hmWanMbus26 54 }

hmWanMbus26Value18		OBJECT-TYPE
			SYNTAX	INTEGER
			MAX-ACCESS	read-only
			STATUS	current
			::= { hmWanMbus26 55 }

hmWanMbus26VIF19		OBJECT-TYPE
			SYNTAX	INTEGER
			MAX-ACCESS	read-only
			STATUS	current
			::= { hmWanMbus26 56 }

hmWanMbus26Value19		OBJECT-TYPE
			SYNTAX	INTEGER
			MAX-ACCESS	read-only
			STATUS	current
			::= { hmWanMbus26 57 }

hmWanMbus26VIF1A		OBJECT-TYPE
			SYNTAX	INTEGER
			MAX-ACCESS	read-only
			STATUS	current
			::= { hmWanMbus26 58 }

hmWanMbus26Value1A		OBJECT-TYPE
			SYNTAX	INTEGER
			MAX-ACCESS	read-only
			STATUS	current
			::= { hmWanMbus26 59 }

hmWanMbus26VIF1B		OBJECT-TYPE
			SYNTAX	INTEGER
			MAX-ACCESS	read-only
			STATUS	current
			::= { hmWanMbus26 60 }

hmWanMbus26Value1B		OBJECT-TYPE
			SYNTAX	INTEGER
			MAX-ACCESS	read-only
			STATUS	current
			::= { hmWanMbus26 61 }

hmWanMbus26VIF1C		OBJECT-TYPE
			SYNTAX	INTEGER
			MAX-ACCESS	read-only
			STATUS	current
			::= { hmWanMbus26 62 }

hmWanMbus26Value1C		OBJECT-TYPE
			SYNTAX	INTEGER
			MAX-ACCESS	read-only
			STATUS	current
			::= { hmWanMbus26 63 }

hmWanMbus26VIF1D		OBJECT-TYPE
			SYNTAX	INTEGER
			MAX-ACCESS	read-only
			STATUS	current
			::= { hmWanMbus26 64 }

hmWanMbus26Value1D		OBJECT-TYPE
			SYNTAX	INTEGER
			MAX-ACCESS	read-only
			STATUS	current
			::= { hmWanMbus26 65 }

hmWanMbus26VIF1E		OBJECT-TYPE
			SYNTAX	INTEGER
			MAX-ACCESS	read-only
			STATUS	current
			::= { hmWanMbus26 66 }

hmWanMbus26Value1E		OBJECT-TYPE
			SYNTAX	INTEGER
			MAX-ACCESS	read-only
			STATUS	current
			::= { hmWanMbus26 67 }

hmWanMbus26VIF1F		OBJECT-TYPE
			SYNTAX	INTEGER
			MAX-ACCESS	read-only
			STATUS	current
			::= { hmWanMbus26 68 }

hmWanMbus26Value1F		OBJECT-TYPE
			SYNTAX	INTEGER
			MAX-ACCESS	read-only
			STATUS	current
			::= { hmWanMbus26 69 }

hmWanMbus26VIF20		OBJECT-TYPE
			SYNTAX	INTEGER
			MAX-ACCESS	read-only
			STATUS	current
			::= { hmWanMbus26 70 }

hmWanMbus26Value20		OBJECT-TYPE
			SYNTAX	INTEGER
			MAX-ACCESS	read-only
			STATUS	current
			::= { hmWanMbus26 71 }

hmWanMbus26VIF21		OBJECT-TYPE
			SYNTAX	INTEGER
			MAX-ACCESS	read-only
			STATUS	current
			::= { hmWanMbus26 72 }

hmWanMbus26Value21		OBJECT-TYPE
			SYNTAX	INTEGER
			MAX-ACCESS	read-only
			STATUS	current
			::= { hmWanMbus26 73 }

hmWanMbus26VIF22		OBJECT-TYPE
			SYNTAX	INTEGER
			MAX-ACCESS	read-only
			STATUS	current
			::= { hmWanMbus26 74 }

hmWanMbus26Value22		OBJECT-TYPE
			SYNTAX	INTEGER
			MAX-ACCESS	read-only
			STATUS	current
			::= { hmWanMbus26 75 }

hmWanMbus26VIF23		OBJECT-TYPE
			SYNTAX	INTEGER
			MAX-ACCESS	read-only
			STATUS	current
			::= { hmWanMbus26 76 }

hmWanMbus26Value23		OBJECT-TYPE
			SYNTAX	INTEGER
			MAX-ACCESS	read-only
			STATUS	current
			::= { hmWanMbus26 77 }

hmWanMbus26VIF24		OBJECT-TYPE
			SYNTAX	INTEGER
			MAX-ACCESS	read-only
			STATUS	current
			::= { hmWanMbus26 78 }

hmWanMbus26Value24		OBJECT-TYPE
			SYNTAX	INTEGER
			MAX-ACCESS	read-only
			STATUS	current
			::= { hmWanMbus26 79 }

hmWanMbus26VIF25		OBJECT-TYPE
			SYNTAX	INTEGER
			MAX-ACCESS	read-only
			STATUS	current
			::= { hmWanMbus26 80 }

hmWanMbus26Value25		OBJECT-TYPE
			SYNTAX	INTEGER
			MAX-ACCESS	read-only
			STATUS	current
			::= { hmWanMbus26 81 }

hmWanMbus26VIF26		OBJECT-TYPE
			SYNTAX	INTEGER
			MAX-ACCESS	read-only
			STATUS	current
			::= { hmWanMbus26 82 }

hmWanMbus26Value26		OBJECT-TYPE
			SYNTAX	INTEGER
			MAX-ACCESS	read-only
			STATUS	current
			::= { hmWanMbus26 83 }

hmWanMbus26VIF27		OBJECT-TYPE
			SYNTAX	INTEGER
			MAX-ACCESS	read-only
			STATUS	current
			::= { hmWanMbus26 84 }

hmWanMbus26Value27		OBJECT-TYPE
			SYNTAX	INTEGER
			MAX-ACCESS	read-only
			STATUS	current
			::= { hmWanMbus26 85 }

hmWanMbus26VIF28		OBJECT-TYPE
			SYNTAX	INTEGER
			MAX-ACCESS	read-only
			STATUS	current
			::= { hmWanMbus26 86 }

hmWanMbus26Value28		OBJECT-TYPE
			SYNTAX	INTEGER
			MAX-ACCESS	read-only
			STATUS	current
			::= { hmWanMbus26 87 }

hmWanMbus26VIF29		OBJECT-TYPE
			SYNTAX	INTEGER
			MAX-ACCESS	read-only
			STATUS	current
			::= { hmWanMbus26 88 }

hmWanMbus26Value29		OBJECT-TYPE
			SYNTAX	INTEGER
			MAX-ACCESS	read-only
			STATUS	current
			::= { hmWanMbus26 89 }

hmWanMbus26VIF2A		OBJECT-TYPE
			SYNTAX	INTEGER
			MAX-ACCESS	read-only
			STATUS	current
			::= { hmWanMbus26 90 }

hmWanMbus26Value2A		OBJECT-TYPE
			SYNTAX	INTEGER
			MAX-ACCESS	read-only
			STATUS	current
			::= { hmWanMbus26 91 }

hmWanMbus26VIF2B		OBJECT-TYPE
			SYNTAX	INTEGER
			MAX-ACCESS	read-only
			STATUS	current
			::= { hmWanMbus26 92 }

hmWanMbus26Value2B		OBJECT-TYPE
			SYNTAX	INTEGER
			MAX-ACCESS	read-only
			STATUS	current
			::= { hmWanMbus26 93 }

hmWanMbus26VIF2C		OBJECT-TYPE
			SYNTAX	INTEGER
			MAX-ACCESS	read-only
			STATUS	current
			::= { hmWanMbus26 94 }

hmWanMbus26Value2C		OBJECT-TYPE
			SYNTAX	INTEGER
			MAX-ACCESS	read-only
			STATUS	current
			::= { hmWanMbus26 95 }

hmWanMbus26VIF2D		OBJECT-TYPE
			SYNTAX	INTEGER
			MAX-ACCESS	read-only
			STATUS	current
			::= { hmWanMbus26 96 }

hmWanMbus26Value2D		OBJECT-TYPE
			SYNTAX	INTEGER
			MAX-ACCESS	read-only
			STATUS	current
			::= { hmWanMbus26 97 }

hmWanMbus26VIF2E		OBJECT-TYPE
			SYNTAX	INTEGER
			MAX-ACCESS	read-only
			STATUS	current
			::= { hmWanMbus26 98 }

hmWanMbus26Value2E		OBJECT-TYPE
			SYNTAX	INTEGER
			MAX-ACCESS	read-only
			STATUS	current
			::= { hmWanMbus26 99 }

hmWanMbus26VIF2F		OBJECT-TYPE
			SYNTAX	INTEGER
			MAX-ACCESS	read-only
			STATUS	current
			::= { hmWanMbus26 100 }

hmWanMbus26Value2F		OBJECT-TYPE
			SYNTAX	INTEGER
			MAX-ACCESS	read-only
			STATUS	current
			::= { hmWanMbus26 101 }

hmWanMbus27			OBJECT IDENTIFIER ::= { hmWanMbus 39 }

hmWanMbus27IdNumber		OBJECT-TYPE
			SYNTAX	Gauge32
			MAX-ACCESS	read-only
			STATUS	current
			::= { hmWanMbus27 1 }

hmWanMbus27Manufacturer	OBJECT-TYPE
			SYNTAX	Gauge32
			MAX-ACCESS	read-only
			STATUS	current
			::= { hmWanMbus27 2 }

hmWanMbus27Version		OBJECT-TYPE
			SYNTAX	Gauge32
			MAX-ACCESS	read-only
			STATUS	current
			::= { hmWanMbus27 3 }

hmWanMbus27Medium		OBJECT-TYPE
			SYNTAX	Gauge32
			MAX-ACCESS	read-only
			STATUS	current
			::= { hmWanMbus27 4 }

hmWanMbus27Status		OBJECT-TYPE
			SYNTAX	Gauge32
			MAX-ACCESS	read-only
			STATUS	current
			::= { hmWanMbus27 5 }

hmWanMbus27VIF00		OBJECT-TYPE
			SYNTAX	INTEGER
			MAX-ACCESS	read-only
			STATUS	current
			::= { hmWanMbus27 6 }

hmWanMbus27Value00		OBJECT-TYPE
			SYNTAX	INTEGER
			MAX-ACCESS	read-only
			STATUS	current
			::= { hmWanMbus27 7 }

hmWanMbus27VIF01		OBJECT-TYPE
			SYNTAX	INTEGER
			MAX-ACCESS	read-only
			STATUS	current
			::= { hmWanMbus27 8 }

hmWanMbus27Value01		OBJECT-TYPE
			SYNTAX	INTEGER
			MAX-ACCESS	read-only
			STATUS	current
			::= { hmWanMbus27 9 }

hmWanMbus27VIF02		OBJECT-TYPE
			SYNTAX	INTEGER
			MAX-ACCESS	read-only
			STATUS	current
			::= { hmWanMbus27 10 }

hmWanMbus27Value02		OBJECT-TYPE
			SYNTAX	INTEGER
			MAX-ACCESS	read-only
			STATUS	current
			::= { hmWanMbus27 11 }

hmWanMbus27VIF03		OBJECT-TYPE
			SYNTAX	INTEGER
			MAX-ACCESS	read-only
			STATUS	current
			::= { hmWanMbus27 12 }

hmWanMbus27Value03		OBJECT-TYPE
			SYNTAX	INTEGER
			MAX-ACCESS	read-only
			STATUS	current
			::= { hmWanMbus27 13 }

hmWanMbus27VIF04		OBJECT-TYPE
			SYNTAX	INTEGER
			MAX-ACCESS	read-only
			STATUS	current
			::= { hmWanMbus27 14 }

hmWanMbus27Value04		OBJECT-TYPE
			SYNTAX	INTEGER
			MAX-ACCESS	read-only
			STATUS	current
			::= { hmWanMbus27 15 }

hmWanMbus27VIF05		OBJECT-TYPE
			SYNTAX	INTEGER
			MAX-ACCESS	read-only
			STATUS	current
			::= { hmWanMbus27 16 }

hmWanMbus27Value05		OBJECT-TYPE
			SYNTAX	INTEGER
			MAX-ACCESS	read-only
			STATUS	current
			::= { hmWanMbus27 17 }

hmWanMbus27VIF06		OBJECT-TYPE
			SYNTAX	INTEGER
			MAX-ACCESS	read-only
			STATUS	current
			::= { hmWanMbus27 18 }

hmWanMbus27Value06		OBJECT-TYPE
			SYNTAX	INTEGER
			MAX-ACCESS	read-only
			STATUS	current
			::= { hmWanMbus27 19 }

hmWanMbus27VIF07		OBJECT-TYPE
			SYNTAX	INTEGER
			MAX-ACCESS	read-only
			STATUS	current
			::= { hmWanMbus27 20 }

hmWanMbus27Value07		OBJECT-TYPE
			SYNTAX	INTEGER
			MAX-ACCESS	read-only
			STATUS	current
			::= { hmWanMbus27 21 }

hmWanMbus27VIF08		OBJECT-TYPE
			SYNTAX	INTEGER
			MAX-ACCESS	read-only
			STATUS	current
			::= { hmWanMbus27 22 }

hmWanMbus27Value08		OBJECT-TYPE
			SYNTAX	INTEGER
			MAX-ACCESS	read-only
			STATUS	current
			::= { hmWanMbus27 23 }

hmWanMbus27VIF09		OBJECT-TYPE
			SYNTAX	INTEGER
			MAX-ACCESS	read-only
			STATUS	current
			::= { hmWanMbus27 24 }

hmWanMbus27Value09		OBJECT-TYPE
			SYNTAX	INTEGER
			MAX-ACCESS	read-only
			STATUS	current
			::= { hmWanMbus27 25 }

hmWanMbus27VIF0A		OBJECT-TYPE
			SYNTAX	INTEGER
			MAX-ACCESS	read-only
			STATUS	current
			::= { hmWanMbus27 26 }

hmWanMbus27Value0A		OBJECT-TYPE
			SYNTAX	INTEGER
			MAX-ACCESS	read-only
			STATUS	current
			::= { hmWanMbus27 27 }

hmWanMbus27VIF0B		OBJECT-TYPE
			SYNTAX	INTEGER
			MAX-ACCESS	read-only
			STATUS	current
			::= { hmWanMbus27 28 }

hmWanMbus27Value0B		OBJECT-TYPE
			SYNTAX	INTEGER
			MAX-ACCESS	read-only
			STATUS	current
			::= { hmWanMbus27 29 }

hmWanMbus27VIF0C		OBJECT-TYPE
			SYNTAX	INTEGER
			MAX-ACCESS	read-only
			STATUS	current
			::= { hmWanMbus27 30 }

hmWanMbus27Value0C		OBJECT-TYPE
			SYNTAX	INTEGER
			MAX-ACCESS	read-only
			STATUS	current
			::= { hmWanMbus27 31 }

hmWanMbus27VIF0D		OBJECT-TYPE
			SYNTAX	INTEGER
			MAX-ACCESS	read-only
			STATUS	current
			::= { hmWanMbus27 32 }

hmWanMbus27Value0D		OBJECT-TYPE
			SYNTAX	INTEGER
			MAX-ACCESS	read-only
			STATUS	current
			::= { hmWanMbus27 33 }

hmWanMbus27VIF0E		OBJECT-TYPE
			SYNTAX	INTEGER
			MAX-ACCESS	read-only
			STATUS	current
			::= { hmWanMbus27 34 }

hmWanMbus27Value0E		OBJECT-TYPE
			SYNTAX	INTEGER
			MAX-ACCESS	read-only
			STATUS	current
			::= { hmWanMbus27 35 }

hmWanMbus27VIF0F		OBJECT-TYPE
			SYNTAX	INTEGER
			MAX-ACCESS	read-only
			STATUS	current
			::= { hmWanMbus27 36 }

hmWanMbus27Value0F		OBJECT-TYPE
			SYNTAX	INTEGER
			MAX-ACCESS	read-only
			STATUS	current
			::= { hmWanMbus27 37 }

hmWanMbus27VIF10		OBJECT-TYPE
			SYNTAX	INTEGER
			MAX-ACCESS	read-only
			STATUS	current
			::= { hmWanMbus27 38 }

hmWanMbus27Value10		OBJECT-TYPE
			SYNTAX	INTEGER
			MAX-ACCESS	read-only
			STATUS	current
			::= { hmWanMbus27 39 }

hmWanMbus27VIF11		OBJECT-TYPE
			SYNTAX	INTEGER
			MAX-ACCESS	read-only
			STATUS	current
			::= { hmWanMbus27 40 }

hmWanMbus27Value11		OBJECT-TYPE
			SYNTAX	INTEGER
			MAX-ACCESS	read-only
			STATUS	current
			::= { hmWanMbus27 41 }

hmWanMbus27VIF12		OBJECT-TYPE
			SYNTAX	INTEGER
			MAX-ACCESS	read-only
			STATUS	current
			::= { hmWanMbus27 42 }

hmWanMbus27Value12		OBJECT-TYPE
			SYNTAX	INTEGER
			MAX-ACCESS	read-only
			STATUS	current
			::= { hmWanMbus27 43 }

hmWanMbus27VIF13		OBJECT-TYPE
			SYNTAX	INTEGER
			MAX-ACCESS	read-only
			STATUS	current
			::= { hmWanMbus27 44 }

hmWanMbus27Value13		OBJECT-TYPE
			SYNTAX	INTEGER
			MAX-ACCESS	read-only
			STATUS	current
			::= { hmWanMbus27 45 }

hmWanMbus27VIF14		OBJECT-TYPE
			SYNTAX	INTEGER
			MAX-ACCESS	read-only
			STATUS	current
			::= { hmWanMbus27 46 }

hmWanMbus27Value14		OBJECT-TYPE
			SYNTAX	INTEGER
			MAX-ACCESS	read-only
			STATUS	current
			::= { hmWanMbus27 47 }

hmWanMbus27VIF15		OBJECT-TYPE
			SYNTAX	INTEGER
			MAX-ACCESS	read-only
			STATUS	current
			::= { hmWanMbus27 48 }

hmWanMbus27Value15		OBJECT-TYPE
			SYNTAX	INTEGER
			MAX-ACCESS	read-only
			STATUS	current
			::= { hmWanMbus27 49 }

hmWanMbus27VIF16		OBJECT-TYPE
			SYNTAX	INTEGER
			MAX-ACCESS	read-only
			STATUS	current
			::= { hmWanMbus27 50 }

hmWanMbus27Value16		OBJECT-TYPE
			SYNTAX	INTEGER
			MAX-ACCESS	read-only
			STATUS	current
			::= { hmWanMbus27 51 }

hmWanMbus27VIF17		OBJECT-TYPE
			SYNTAX	INTEGER
			MAX-ACCESS	read-only
			STATUS	current
			::= { hmWanMbus27 52 }

hmWanMbus27Value17		OBJECT-TYPE
			SYNTAX	INTEGER
			MAX-ACCESS	read-only
			STATUS	current
			::= { hmWanMbus27 53 }

hmWanMbus27VIF18		OBJECT-TYPE
			SYNTAX	INTEGER
			MAX-ACCESS	read-only
			STATUS	current
			::= { hmWanMbus27 54 }

hmWanMbus27Value18		OBJECT-TYPE
			SYNTAX	INTEGER
			MAX-ACCESS	read-only
			STATUS	current
			::= { hmWanMbus27 55 }

hmWanMbus27VIF19		OBJECT-TYPE
			SYNTAX	INTEGER
			MAX-ACCESS	read-only
			STATUS	current
			::= { hmWanMbus27 56 }

hmWanMbus27Value19		OBJECT-TYPE
			SYNTAX	INTEGER
			MAX-ACCESS	read-only
			STATUS	current
			::= { hmWanMbus27 57 }

hmWanMbus27VIF1A		OBJECT-TYPE
			SYNTAX	INTEGER
			MAX-ACCESS	read-only
			STATUS	current
			::= { hmWanMbus27 58 }

hmWanMbus27Value1A		OBJECT-TYPE
			SYNTAX	INTEGER
			MAX-ACCESS	read-only
			STATUS	current
			::= { hmWanMbus27 59 }

hmWanMbus27VIF1B		OBJECT-TYPE
			SYNTAX	INTEGER
			MAX-ACCESS	read-only
			STATUS	current
			::= { hmWanMbus27 60 }

hmWanMbus27Value1B		OBJECT-TYPE
			SYNTAX	INTEGER
			MAX-ACCESS	read-only
			STATUS	current
			::= { hmWanMbus27 61 }

hmWanMbus27VIF1C		OBJECT-TYPE
			SYNTAX	INTEGER
			MAX-ACCESS	read-only
			STATUS	current
			::= { hmWanMbus27 62 }

hmWanMbus27Value1C		OBJECT-TYPE
			SYNTAX	INTEGER
			MAX-ACCESS	read-only
			STATUS	current
			::= { hmWanMbus27 63 }

hmWanMbus27VIF1D		OBJECT-TYPE
			SYNTAX	INTEGER
			MAX-ACCESS	read-only
			STATUS	current
			::= { hmWanMbus27 64 }

hmWanMbus27Value1D		OBJECT-TYPE
			SYNTAX	INTEGER
			MAX-ACCESS	read-only
			STATUS	current
			::= { hmWanMbus27 65 }

hmWanMbus27VIF1E		OBJECT-TYPE
			SYNTAX	INTEGER
			MAX-ACCESS	read-only
			STATUS	current
			::= { hmWanMbus27 66 }

hmWanMbus27Value1E		OBJECT-TYPE
			SYNTAX	INTEGER
			MAX-ACCESS	read-only
			STATUS	current
			::= { hmWanMbus27 67 }

hmWanMbus27VIF1F		OBJECT-TYPE
			SYNTAX	INTEGER
			MAX-ACCESS	read-only
			STATUS	current
			::= { hmWanMbus27 68 }

hmWanMbus27Value1F		OBJECT-TYPE
			SYNTAX	INTEGER
			MAX-ACCESS	read-only
			STATUS	current
			::= { hmWanMbus27 69 }

hmWanMbus27VIF20		OBJECT-TYPE
			SYNTAX	INTEGER
			MAX-ACCESS	read-only
			STATUS	current
			::= { hmWanMbus27 70 }

hmWanMbus27Value20		OBJECT-TYPE
			SYNTAX	INTEGER
			MAX-ACCESS	read-only
			STATUS	current
			::= { hmWanMbus27 71 }

hmWanMbus27VIF21		OBJECT-TYPE
			SYNTAX	INTEGER
			MAX-ACCESS	read-only
			STATUS	current
			::= { hmWanMbus27 72 }

hmWanMbus27Value21		OBJECT-TYPE
			SYNTAX	INTEGER
			MAX-ACCESS	read-only
			STATUS	current
			::= { hmWanMbus27 73 }

hmWanMbus27VIF22		OBJECT-TYPE
			SYNTAX	INTEGER
			MAX-ACCESS	read-only
			STATUS	current
			::= { hmWanMbus27 74 }

hmWanMbus27Value22		OBJECT-TYPE
			SYNTAX	INTEGER
			MAX-ACCESS	read-only
			STATUS	current
			::= { hmWanMbus27 75 }

hmWanMbus27VIF23		OBJECT-TYPE
			SYNTAX	INTEGER
			MAX-ACCESS	read-only
			STATUS	current
			::= { hmWanMbus27 76 }

hmWanMbus27Value23		OBJECT-TYPE
			SYNTAX	INTEGER
			MAX-ACCESS	read-only
			STATUS	current
			::= { hmWanMbus27 77 }

hmWanMbus27VIF24		OBJECT-TYPE
			SYNTAX	INTEGER
			MAX-ACCESS	read-only
			STATUS	current
			::= { hmWanMbus27 78 }

hmWanMbus27Value24		OBJECT-TYPE
			SYNTAX	INTEGER
			MAX-ACCESS	read-only
			STATUS	current
			::= { hmWanMbus27 79 }

hmWanMbus27VIF25		OBJECT-TYPE
			SYNTAX	INTEGER
			MAX-ACCESS	read-only
			STATUS	current
			::= { hmWanMbus27 80 }

hmWanMbus27Value25		OBJECT-TYPE
			SYNTAX	INTEGER
			MAX-ACCESS	read-only
			STATUS	current
			::= { hmWanMbus27 81 }

hmWanMbus27VIF26		OBJECT-TYPE
			SYNTAX	INTEGER
			MAX-ACCESS	read-only
			STATUS	current
			::= { hmWanMbus27 82 }

hmWanMbus27Value26		OBJECT-TYPE
			SYNTAX	INTEGER
			MAX-ACCESS	read-only
			STATUS	current
			::= { hmWanMbus27 83 }

hmWanMbus27VIF27		OBJECT-TYPE
			SYNTAX	INTEGER
			MAX-ACCESS	read-only
			STATUS	current
			::= { hmWanMbus27 84 }

hmWanMbus27Value27		OBJECT-TYPE
			SYNTAX	INTEGER
			MAX-ACCESS	read-only
			STATUS	current
			::= { hmWanMbus27 85 }

hmWanMbus27VIF28		OBJECT-TYPE
			SYNTAX	INTEGER
			MAX-ACCESS	read-only
			STATUS	current
			::= { hmWanMbus27 86 }

hmWanMbus27Value28		OBJECT-TYPE
			SYNTAX	INTEGER
			MAX-ACCESS	read-only
			STATUS	current
			::= { hmWanMbus27 87 }

hmWanMbus27VIF29		OBJECT-TYPE
			SYNTAX	INTEGER
			MAX-ACCESS	read-only
			STATUS	current
			::= { hmWanMbus27 88 }

hmWanMbus27Value29		OBJECT-TYPE
			SYNTAX	INTEGER
			MAX-ACCESS	read-only
			STATUS	current
			::= { hmWanMbus27 89 }

hmWanMbus27VIF2A		OBJECT-TYPE
			SYNTAX	INTEGER
			MAX-ACCESS	read-only
			STATUS	current
			::= { hmWanMbus27 90 }

hmWanMbus27Value2A		OBJECT-TYPE
			SYNTAX	INTEGER
			MAX-ACCESS	read-only
			STATUS	current
			::= { hmWanMbus27 91 }

hmWanMbus27VIF2B		OBJECT-TYPE
			SYNTAX	INTEGER
			MAX-ACCESS	read-only
			STATUS	current
			::= { hmWanMbus27 92 }

hmWanMbus27Value2B		OBJECT-TYPE
			SYNTAX	INTEGER
			MAX-ACCESS	read-only
			STATUS	current
			::= { hmWanMbus27 93 }

hmWanMbus27VIF2C		OBJECT-TYPE
			SYNTAX	INTEGER
			MAX-ACCESS	read-only
			STATUS	current
			::= { hmWanMbus27 94 }

hmWanMbus27Value2C		OBJECT-TYPE
			SYNTAX	INTEGER
			MAX-ACCESS	read-only
			STATUS	current
			::= { hmWanMbus27 95 }

hmWanMbus27VIF2D		OBJECT-TYPE
			SYNTAX	INTEGER
			MAX-ACCESS	read-only
			STATUS	current
			::= { hmWanMbus27 96 }

hmWanMbus27Value2D		OBJECT-TYPE
			SYNTAX	INTEGER
			MAX-ACCESS	read-only
			STATUS	current
			::= { hmWanMbus27 97 }

hmWanMbus27VIF2E		OBJECT-TYPE
			SYNTAX	INTEGER
			MAX-ACCESS	read-only
			STATUS	current
			::= { hmWanMbus27 98 }

hmWanMbus27Value2E		OBJECT-TYPE
			SYNTAX	INTEGER
			MAX-ACCESS	read-only
			STATUS	current
			::= { hmWanMbus27 99 }

hmWanMbus27VIF2F		OBJECT-TYPE
			SYNTAX	INTEGER
			MAX-ACCESS	read-only
			STATUS	current
			::= { hmWanMbus27 100 }

hmWanMbus27Value2F		OBJECT-TYPE
			SYNTAX	INTEGER
			MAX-ACCESS	read-only
			STATUS	current
			::= { hmWanMbus27 101 }

hmWanMbus28			OBJECT IDENTIFIER ::= { hmWanMbus 40 }

hmWanMbus28IdNumber		OBJECT-TYPE
			SYNTAX	Gauge32
			MAX-ACCESS	read-only
			STATUS	current
			::= { hmWanMbus28 1 }

hmWanMbus28Manufacturer	OBJECT-TYPE
			SYNTAX	Gauge32
			MAX-ACCESS	read-only
			STATUS	current
			::= { hmWanMbus28 2 }

hmWanMbus28Version		OBJECT-TYPE
			SYNTAX	Gauge32
			MAX-ACCESS	read-only
			STATUS	current
			::= { hmWanMbus28 3 }

hmWanMbus28Medium		OBJECT-TYPE
			SYNTAX	Gauge32
			MAX-ACCESS	read-only
			STATUS	current
			::= { hmWanMbus28 4 }

hmWanMbus28Status		OBJECT-TYPE
			SYNTAX	Gauge32
			MAX-ACCESS	read-only
			STATUS	current
			::= { hmWanMbus28 5 }

hmWanMbus28VIF00		OBJECT-TYPE
			SYNTAX	INTEGER
			MAX-ACCESS	read-only
			STATUS	current
			::= { hmWanMbus28 6 }

hmWanMbus28Value00		OBJECT-TYPE
			SYNTAX	INTEGER
			MAX-ACCESS	read-only
			STATUS	current
			::= { hmWanMbus28 7 }

hmWanMbus28VIF01		OBJECT-TYPE
			SYNTAX	INTEGER
			MAX-ACCESS	read-only
			STATUS	current
			::= { hmWanMbus28 8 }

hmWanMbus28Value01		OBJECT-TYPE
			SYNTAX	INTEGER
			MAX-ACCESS	read-only
			STATUS	current
			::= { hmWanMbus28 9 }

hmWanMbus28VIF02		OBJECT-TYPE
			SYNTAX	INTEGER
			MAX-ACCESS	read-only
			STATUS	current
			::= { hmWanMbus28 10 }

hmWanMbus28Value02		OBJECT-TYPE
			SYNTAX	INTEGER
			MAX-ACCESS	read-only
			STATUS	current
			::= { hmWanMbus28 11 }

hmWanMbus28VIF03		OBJECT-TYPE
			SYNTAX	INTEGER
			MAX-ACCESS	read-only
			STATUS	current
			::= { hmWanMbus28 12 }

hmWanMbus28Value03		OBJECT-TYPE
			SYNTAX	INTEGER
			MAX-ACCESS	read-only
			STATUS	current
			::= { hmWanMbus28 13 }

hmWanMbus28VIF04		OBJECT-TYPE
			SYNTAX	INTEGER
			MAX-ACCESS	read-only
			STATUS	current
			::= { hmWanMbus28 14 }

hmWanMbus28Value04		OBJECT-TYPE
			SYNTAX	INTEGER
			MAX-ACCESS	read-only
			STATUS	current
			::= { hmWanMbus28 15 }

hmWanMbus28VIF05		OBJECT-TYPE
			SYNTAX	INTEGER
			MAX-ACCESS	read-only
			STATUS	current
			::= { hmWanMbus28 16 }

hmWanMbus28Value05		OBJECT-TYPE
			SYNTAX	INTEGER
			MAX-ACCESS	read-only
			STATUS	current
			::= { hmWanMbus28 17 }

hmWanMbus28VIF06		OBJECT-TYPE
			SYNTAX	INTEGER
			MAX-ACCESS	read-only
			STATUS	current
			::= { hmWanMbus28 18 }

hmWanMbus28Value06		OBJECT-TYPE
			SYNTAX	INTEGER
			MAX-ACCESS	read-only
			STATUS	current
			::= { hmWanMbus28 19 }

hmWanMbus28VIF07		OBJECT-TYPE
			SYNTAX	INTEGER
			MAX-ACCESS	read-only
			STATUS	current
			::= { hmWanMbus28 20 }

hmWanMbus28Value07		OBJECT-TYPE
			SYNTAX	INTEGER
			MAX-ACCESS	read-only
			STATUS	current
			::= { hmWanMbus28 21 }

hmWanMbus28VIF08		OBJECT-TYPE
			SYNTAX	INTEGER
			MAX-ACCESS	read-only
			STATUS	current
			::= { hmWanMbus28 22 }

hmWanMbus28Value08		OBJECT-TYPE
			SYNTAX	INTEGER
			MAX-ACCESS	read-only
			STATUS	current
			::= { hmWanMbus28 23 }

hmWanMbus28VIF09		OBJECT-TYPE
			SYNTAX	INTEGER
			MAX-ACCESS	read-only
			STATUS	current
			::= { hmWanMbus28 24 }

hmWanMbus28Value09		OBJECT-TYPE
			SYNTAX	INTEGER
			MAX-ACCESS	read-only
			STATUS	current
			::= { hmWanMbus28 25 }

hmWanMbus28VIF0A		OBJECT-TYPE
			SYNTAX	INTEGER
			MAX-ACCESS	read-only
			STATUS	current
			::= { hmWanMbus28 26 }

hmWanMbus28Value0A		OBJECT-TYPE
			SYNTAX	INTEGER
			MAX-ACCESS	read-only
			STATUS	current
			::= { hmWanMbus28 27 }

hmWanMbus28VIF0B		OBJECT-TYPE
			SYNTAX	INTEGER
			MAX-ACCESS	read-only
			STATUS	current
			::= { hmWanMbus28 28 }

hmWanMbus28Value0B		OBJECT-TYPE
			SYNTAX	INTEGER
			MAX-ACCESS	read-only
			STATUS	current
			::= { hmWanMbus28 29 }

hmWanMbus28VIF0C		OBJECT-TYPE
			SYNTAX	INTEGER
			MAX-ACCESS	read-only
			STATUS	current
			::= { hmWanMbus28 30 }

hmWanMbus28Value0C		OBJECT-TYPE
			SYNTAX	INTEGER
			MAX-ACCESS	read-only
			STATUS	current
			::= { hmWanMbus28 31 }

hmWanMbus28VIF0D		OBJECT-TYPE
			SYNTAX	INTEGER
			MAX-ACCESS	read-only
			STATUS	current
			::= { hmWanMbus28 32 }

hmWanMbus28Value0D		OBJECT-TYPE
			SYNTAX	INTEGER
			MAX-ACCESS	read-only
			STATUS	current
			::= { hmWanMbus28 33 }

hmWanMbus28VIF0E		OBJECT-TYPE
			SYNTAX	INTEGER
			MAX-ACCESS	read-only
			STATUS	current
			::= { hmWanMbus28 34 }

hmWanMbus28Value0E		OBJECT-TYPE
			SYNTAX	INTEGER
			MAX-ACCESS	read-only
			STATUS	current
			::= { hmWanMbus28 35 }

hmWanMbus28VIF0F		OBJECT-TYPE
			SYNTAX	INTEGER
			MAX-ACCESS	read-only
			STATUS	current
			::= { hmWanMbus28 36 }

hmWanMbus28Value0F		OBJECT-TYPE
			SYNTAX	INTEGER
			MAX-ACCESS	read-only
			STATUS	current
			::= { hmWanMbus28 37 }

hmWanMbus28VIF10		OBJECT-TYPE
			SYNTAX	INTEGER
			MAX-ACCESS	read-only
			STATUS	current
			::= { hmWanMbus28 38 }

hmWanMbus28Value10		OBJECT-TYPE
			SYNTAX	INTEGER
			MAX-ACCESS	read-only
			STATUS	current
			::= { hmWanMbus28 39 }

hmWanMbus28VIF11		OBJECT-TYPE
			SYNTAX	INTEGER
			MAX-ACCESS	read-only
			STATUS	current
			::= { hmWanMbus28 40 }

hmWanMbus28Value11		OBJECT-TYPE
			SYNTAX	INTEGER
			MAX-ACCESS	read-only
			STATUS	current
			::= { hmWanMbus28 41 }

hmWanMbus28VIF12		OBJECT-TYPE
			SYNTAX	INTEGER
			MAX-ACCESS	read-only
			STATUS	current
			::= { hmWanMbus28 42 }

hmWanMbus28Value12		OBJECT-TYPE
			SYNTAX	INTEGER
			MAX-ACCESS	read-only
			STATUS	current
			::= { hmWanMbus28 43 }

hmWanMbus28VIF13		OBJECT-TYPE
			SYNTAX	INTEGER
			MAX-ACCESS	read-only
			STATUS	current
			::= { hmWanMbus28 44 }

hmWanMbus28Value13		OBJECT-TYPE
			SYNTAX	INTEGER
			MAX-ACCESS	read-only
			STATUS	current
			::= { hmWanMbus28 45 }

hmWanMbus28VIF14		OBJECT-TYPE
			SYNTAX	INTEGER
			MAX-ACCESS	read-only
			STATUS	current
			::= { hmWanMbus28 46 }

hmWanMbus28Value14		OBJECT-TYPE
			SYNTAX	INTEGER
			MAX-ACCESS	read-only
			STATUS	current
			::= { hmWanMbus28 47 }

hmWanMbus28VIF15		OBJECT-TYPE
			SYNTAX	INTEGER
			MAX-ACCESS	read-only
			STATUS	current
			::= { hmWanMbus28 48 }

hmWanMbus28Value15		OBJECT-TYPE
			SYNTAX	INTEGER
			MAX-ACCESS	read-only
			STATUS	current
			::= { hmWanMbus28 49 }

hmWanMbus28VIF16		OBJECT-TYPE
			SYNTAX	INTEGER
			MAX-ACCESS	read-only
			STATUS	current
			::= { hmWanMbus28 50 }

hmWanMbus28Value16		OBJECT-TYPE
			SYNTAX	INTEGER
			MAX-ACCESS	read-only
			STATUS	current
			::= { hmWanMbus28 51 }

hmWanMbus28VIF17		OBJECT-TYPE
			SYNTAX	INTEGER
			MAX-ACCESS	read-only
			STATUS	current
			::= { hmWanMbus28 52 }

hmWanMbus28Value17		OBJECT-TYPE
			SYNTAX	INTEGER
			MAX-ACCESS	read-only
			STATUS	current
			::= { hmWanMbus28 53 }

hmWanMbus28VIF18		OBJECT-TYPE
			SYNTAX	INTEGER
			MAX-ACCESS	read-only
			STATUS	current
			::= { hmWanMbus28 54 }

hmWanMbus28Value18		OBJECT-TYPE
			SYNTAX	INTEGER
			MAX-ACCESS	read-only
			STATUS	current
			::= { hmWanMbus28 55 }

hmWanMbus28VIF19		OBJECT-TYPE
			SYNTAX	INTEGER
			MAX-ACCESS	read-only
			STATUS	current
			::= { hmWanMbus28 56 }

hmWanMbus28Value19		OBJECT-TYPE
			SYNTAX	INTEGER
			MAX-ACCESS	read-only
			STATUS	current
			::= { hmWanMbus28 57 }

hmWanMbus28VIF1A		OBJECT-TYPE
			SYNTAX	INTEGER
			MAX-ACCESS	read-only
			STATUS	current
			::= { hmWanMbus28 58 }

hmWanMbus28Value1A		OBJECT-TYPE
			SYNTAX	INTEGER
			MAX-ACCESS	read-only
			STATUS	current
			::= { hmWanMbus28 59 }

hmWanMbus28VIF1B		OBJECT-TYPE
			SYNTAX	INTEGER
			MAX-ACCESS	read-only
			STATUS	current
			::= { hmWanMbus28 60 }

hmWanMbus28Value1B		OBJECT-TYPE
			SYNTAX	INTEGER
			MAX-ACCESS	read-only
			STATUS	current
			::= { hmWanMbus28 61 }

hmWanMbus28VIF1C		OBJECT-TYPE
			SYNTAX	INTEGER
			MAX-ACCESS	read-only
			STATUS	current
			::= { hmWanMbus28 62 }

hmWanMbus28Value1C		OBJECT-TYPE
			SYNTAX	INTEGER
			MAX-ACCESS	read-only
			STATUS	current
			::= { hmWanMbus28 63 }

hmWanMbus28VIF1D		OBJECT-TYPE
			SYNTAX	INTEGER
			MAX-ACCESS	read-only
			STATUS	current
			::= { hmWanMbus28 64 }

hmWanMbus28Value1D		OBJECT-TYPE
			SYNTAX	INTEGER
			MAX-ACCESS	read-only
			STATUS	current
			::= { hmWanMbus28 65 }

hmWanMbus28VIF1E		OBJECT-TYPE
			SYNTAX	INTEGER
			MAX-ACCESS	read-only
			STATUS	current
			::= { hmWanMbus28 66 }

hmWanMbus28Value1E		OBJECT-TYPE
			SYNTAX	INTEGER
			MAX-ACCESS	read-only
			STATUS	current
			::= { hmWanMbus28 67 }

hmWanMbus28VIF1F		OBJECT-TYPE
			SYNTAX	INTEGER
			MAX-ACCESS	read-only
			STATUS	current
			::= { hmWanMbus28 68 }

hmWanMbus28Value1F		OBJECT-TYPE
			SYNTAX	INTEGER
			MAX-ACCESS	read-only
			STATUS	current
			::= { hmWanMbus28 69 }

hmWanMbus28VIF20		OBJECT-TYPE
			SYNTAX	INTEGER
			MAX-ACCESS	read-only
			STATUS	current
			::= { hmWanMbus28 70 }

hmWanMbus28Value20		OBJECT-TYPE
			SYNTAX	INTEGER
			MAX-ACCESS	read-only
			STATUS	current
			::= { hmWanMbus28 71 }

hmWanMbus28VIF21		OBJECT-TYPE
			SYNTAX	INTEGER
			MAX-ACCESS	read-only
			STATUS	current
			::= { hmWanMbus28 72 }

hmWanMbus28Value21		OBJECT-TYPE
			SYNTAX	INTEGER
			MAX-ACCESS	read-only
			STATUS	current
			::= { hmWanMbus28 73 }

hmWanMbus28VIF22		OBJECT-TYPE
			SYNTAX	INTEGER
			MAX-ACCESS	read-only
			STATUS	current
			::= { hmWanMbus28 74 }

hmWanMbus28Value22		OBJECT-TYPE
			SYNTAX	INTEGER
			MAX-ACCESS	read-only
			STATUS	current
			::= { hmWanMbus28 75 }

hmWanMbus28VIF23		OBJECT-TYPE
			SYNTAX	INTEGER
			MAX-ACCESS	read-only
			STATUS	current
			::= { hmWanMbus28 76 }

hmWanMbus28Value23		OBJECT-TYPE
			SYNTAX	INTEGER
			MAX-ACCESS	read-only
			STATUS	current
			::= { hmWanMbus28 77 }

hmWanMbus28VIF24		OBJECT-TYPE
			SYNTAX	INTEGER
			MAX-ACCESS	read-only
			STATUS	current
			::= { hmWanMbus28 78 }

hmWanMbus28Value24		OBJECT-TYPE
			SYNTAX	INTEGER
			MAX-ACCESS	read-only
			STATUS	current
			::= { hmWanMbus28 79 }

hmWanMbus28VIF25		OBJECT-TYPE
			SYNTAX	INTEGER
			MAX-ACCESS	read-only
			STATUS	current
			::= { hmWanMbus28 80 }

hmWanMbus28Value25		OBJECT-TYPE
			SYNTAX	INTEGER
			MAX-ACCESS	read-only
			STATUS	current
			::= { hmWanMbus28 81 }

hmWanMbus28VIF26		OBJECT-TYPE
			SYNTAX	INTEGER
			MAX-ACCESS	read-only
			STATUS	current
			::= { hmWanMbus28 82 }

hmWanMbus28Value26		OBJECT-TYPE
			SYNTAX	INTEGER
			MAX-ACCESS	read-only
			STATUS	current
			::= { hmWanMbus28 83 }

hmWanMbus28VIF27		OBJECT-TYPE
			SYNTAX	INTEGER
			MAX-ACCESS	read-only
			STATUS	current
			::= { hmWanMbus28 84 }

hmWanMbus28Value27		OBJECT-TYPE
			SYNTAX	INTEGER
			MAX-ACCESS	read-only
			STATUS	current
			::= { hmWanMbus28 85 }

hmWanMbus28VIF28		OBJECT-TYPE
			SYNTAX	INTEGER
			MAX-ACCESS	read-only
			STATUS	current
			::= { hmWanMbus28 86 }

hmWanMbus28Value28		OBJECT-TYPE
			SYNTAX	INTEGER
			MAX-ACCESS	read-only
			STATUS	current
			::= { hmWanMbus28 87 }

hmWanMbus28VIF29		OBJECT-TYPE
			SYNTAX	INTEGER
			MAX-ACCESS	read-only
			STATUS	current
			::= { hmWanMbus28 88 }

hmWanMbus28Value29		OBJECT-TYPE
			SYNTAX	INTEGER
			MAX-ACCESS	read-only
			STATUS	current
			::= { hmWanMbus28 89 }

hmWanMbus28VIF2A		OBJECT-TYPE
			SYNTAX	INTEGER
			MAX-ACCESS	read-only
			STATUS	current
			::= { hmWanMbus28 90 }

hmWanMbus28Value2A		OBJECT-TYPE
			SYNTAX	INTEGER
			MAX-ACCESS	read-only
			STATUS	current
			::= { hmWanMbus28 91 }

hmWanMbus28VIF2B		OBJECT-TYPE
			SYNTAX	INTEGER
			MAX-ACCESS	read-only
			STATUS	current
			::= { hmWanMbus28 92 }

hmWanMbus28Value2B		OBJECT-TYPE
			SYNTAX	INTEGER
			MAX-ACCESS	read-only
			STATUS	current
			::= { hmWanMbus28 93 }

hmWanMbus28VIF2C		OBJECT-TYPE
			SYNTAX	INTEGER
			MAX-ACCESS	read-only
			STATUS	current
			::= { hmWanMbus28 94 }

hmWanMbus28Value2C		OBJECT-TYPE
			SYNTAX	INTEGER
			MAX-ACCESS	read-only
			STATUS	current
			::= { hmWanMbus28 95 }

hmWanMbus28VIF2D		OBJECT-TYPE
			SYNTAX	INTEGER
			MAX-ACCESS	read-only
			STATUS	current
			::= { hmWanMbus28 96 }

hmWanMbus28Value2D		OBJECT-TYPE
			SYNTAX	INTEGER
			MAX-ACCESS	read-only
			STATUS	current
			::= { hmWanMbus28 97 }

hmWanMbus28VIF2E		OBJECT-TYPE
			SYNTAX	INTEGER
			MAX-ACCESS	read-only
			STATUS	current
			::= { hmWanMbus28 98 }

hmWanMbus28Value2E		OBJECT-TYPE
			SYNTAX	INTEGER
			MAX-ACCESS	read-only
			STATUS	current
			::= { hmWanMbus28 99 }

hmWanMbus28VIF2F		OBJECT-TYPE
			SYNTAX	INTEGER
			MAX-ACCESS	read-only
			STATUS	current
			::= { hmWanMbus28 100 }

hmWanMbus28Value2F		OBJECT-TYPE
			SYNTAX	INTEGER
			MAX-ACCESS	read-only
			STATUS	current
			::= { hmWanMbus28 101 }

hmWanMbus29			OBJECT IDENTIFIER ::= { hmWanMbus 41 }

hmWanMbus29IdNumber		OBJECT-TYPE
			SYNTAX	Gauge32
			MAX-ACCESS	read-only
			STATUS	current
			::= { hmWanMbus29 1 }

hmWanMbus29Manufacturer	OBJECT-TYPE
			SYNTAX	Gauge32
			MAX-ACCESS	read-only
			STATUS	current
			::= { hmWanMbus29 2 }

hmWanMbus29Version		OBJECT-TYPE
			SYNTAX	Gauge32
			MAX-ACCESS	read-only
			STATUS	current
			::= { hmWanMbus29 3 }

hmWanMbus29Medium		OBJECT-TYPE
			SYNTAX	Gauge32
			MAX-ACCESS	read-only
			STATUS	current
			::= { hmWanMbus29 4 }

hmWanMbus29Status		OBJECT-TYPE
			SYNTAX	Gauge32
			MAX-ACCESS	read-only
			STATUS	current
			::= { hmWanMbus29 5 }

hmWanMbus29VIF00		OBJECT-TYPE
			SYNTAX	INTEGER
			MAX-ACCESS	read-only
			STATUS	current
			::= { hmWanMbus29 6 }

hmWanMbus29Value00		OBJECT-TYPE
			SYNTAX	INTEGER
			MAX-ACCESS	read-only
			STATUS	current
			::= { hmWanMbus29 7 }

hmWanMbus29VIF01		OBJECT-TYPE
			SYNTAX	INTEGER
			MAX-ACCESS	read-only
			STATUS	current
			::= { hmWanMbus29 8 }

hmWanMbus29Value01		OBJECT-TYPE
			SYNTAX	INTEGER
			MAX-ACCESS	read-only
			STATUS	current
			::= { hmWanMbus29 9 }

hmWanMbus29VIF02		OBJECT-TYPE
			SYNTAX	INTEGER
			MAX-ACCESS	read-only
			STATUS	current
			::= { hmWanMbus29 10 }

hmWanMbus29Value02		OBJECT-TYPE
			SYNTAX	INTEGER
			MAX-ACCESS	read-only
			STATUS	current
			::= { hmWanMbus29 11 }

hmWanMbus29VIF03		OBJECT-TYPE
			SYNTAX	INTEGER
			MAX-ACCESS	read-only
			STATUS	current
			::= { hmWanMbus29 12 }

hmWanMbus29Value03		OBJECT-TYPE
			SYNTAX	INTEGER
			MAX-ACCESS	read-only
			STATUS	current
			::= { hmWanMbus29 13 }

hmWanMbus29VIF04		OBJECT-TYPE
			SYNTAX	INTEGER
			MAX-ACCESS	read-only
			STATUS	current
			::= { hmWanMbus29 14 }

hmWanMbus29Value04		OBJECT-TYPE
			SYNTAX	INTEGER
			MAX-ACCESS	read-only
			STATUS	current
			::= { hmWanMbus29 15 }

hmWanMbus29VIF05		OBJECT-TYPE
			SYNTAX	INTEGER
			MAX-ACCESS	read-only
			STATUS	current
			::= { hmWanMbus29 16 }

hmWanMbus29Value05		OBJECT-TYPE
			SYNTAX	INTEGER
			MAX-ACCESS	read-only
			STATUS	current
			::= { hmWanMbus29 17 }

hmWanMbus29VIF06		OBJECT-TYPE
			SYNTAX	INTEGER
			MAX-ACCESS	read-only
			STATUS	current
			::= { hmWanMbus29 18 }

hmWanMbus29Value06		OBJECT-TYPE
			SYNTAX	INTEGER
			MAX-ACCESS	read-only
			STATUS	current
			::= { hmWanMbus29 19 }

hmWanMbus29VIF07		OBJECT-TYPE
			SYNTAX	INTEGER
			MAX-ACCESS	read-only
			STATUS	current
			::= { hmWanMbus29 20 }

hmWanMbus29Value07		OBJECT-TYPE
			SYNTAX	INTEGER
			MAX-ACCESS	read-only
			STATUS	current
			::= { hmWanMbus29 21 }

hmWanMbus29VIF08		OBJECT-TYPE
			SYNTAX	INTEGER
			MAX-ACCESS	read-only
			STATUS	current
			::= { hmWanMbus29 22 }

hmWanMbus29Value08		OBJECT-TYPE
			SYNTAX	INTEGER
			MAX-ACCESS	read-only
			STATUS	current
			::= { hmWanMbus29 23 }

hmWanMbus29VIF09		OBJECT-TYPE
			SYNTAX	INTEGER
			MAX-ACCESS	read-only
			STATUS	current
			::= { hmWanMbus29 24 }

hmWanMbus29Value09		OBJECT-TYPE
			SYNTAX	INTEGER
			MAX-ACCESS	read-only
			STATUS	current
			::= { hmWanMbus29 25 }

hmWanMbus29VIF0A		OBJECT-TYPE
			SYNTAX	INTEGER
			MAX-ACCESS	read-only
			STATUS	current
			::= { hmWanMbus29 26 }

hmWanMbus29Value0A		OBJECT-TYPE
			SYNTAX	INTEGER
			MAX-ACCESS	read-only
			STATUS	current
			::= { hmWanMbus29 27 }

hmWanMbus29VIF0B		OBJECT-TYPE
			SYNTAX	INTEGER
			MAX-ACCESS	read-only
			STATUS	current
			::= { hmWanMbus29 28 }

hmWanMbus29Value0B		OBJECT-TYPE
			SYNTAX	INTEGER
			MAX-ACCESS	read-only
			STATUS	current
			::= { hmWanMbus29 29 }

hmWanMbus29VIF0C		OBJECT-TYPE
			SYNTAX	INTEGER
			MAX-ACCESS	read-only
			STATUS	current
			::= { hmWanMbus29 30 }

hmWanMbus29Value0C		OBJECT-TYPE
			SYNTAX	INTEGER
			MAX-ACCESS	read-only
			STATUS	current
			::= { hmWanMbus29 31 }

hmWanMbus29VIF0D		OBJECT-TYPE
			SYNTAX	INTEGER
			MAX-ACCESS	read-only
			STATUS	current
			::= { hmWanMbus29 32 }

hmWanMbus29Value0D		OBJECT-TYPE
			SYNTAX	INTEGER
			MAX-ACCESS	read-only
			STATUS	current
			::= { hmWanMbus29 33 }

hmWanMbus29VIF0E		OBJECT-TYPE
			SYNTAX	INTEGER
			MAX-ACCESS	read-only
			STATUS	current
			::= { hmWanMbus29 34 }

hmWanMbus29Value0E		OBJECT-TYPE
			SYNTAX	INTEGER
			MAX-ACCESS	read-only
			STATUS	current
			::= { hmWanMbus29 35 }

hmWanMbus29VIF0F		OBJECT-TYPE
			SYNTAX	INTEGER
			MAX-ACCESS	read-only
			STATUS	current
			::= { hmWanMbus29 36 }

hmWanMbus29Value0F		OBJECT-TYPE
			SYNTAX	INTEGER
			MAX-ACCESS	read-only
			STATUS	current
			::= { hmWanMbus29 37 }

hmWanMbus29VIF10		OBJECT-TYPE
			SYNTAX	INTEGER
			MAX-ACCESS	read-only
			STATUS	current
			::= { hmWanMbus29 38 }

hmWanMbus29Value10		OBJECT-TYPE
			SYNTAX	INTEGER
			MAX-ACCESS	read-only
			STATUS	current
			::= { hmWanMbus29 39 }

hmWanMbus29VIF11		OBJECT-TYPE
			SYNTAX	INTEGER
			MAX-ACCESS	read-only
			STATUS	current
			::= { hmWanMbus29 40 }

hmWanMbus29Value11		OBJECT-TYPE
			SYNTAX	INTEGER
			MAX-ACCESS	read-only
			STATUS	current
			::= { hmWanMbus29 41 }

hmWanMbus29VIF12		OBJECT-TYPE
			SYNTAX	INTEGER
			MAX-ACCESS	read-only
			STATUS	current
			::= { hmWanMbus29 42 }

hmWanMbus29Value12		OBJECT-TYPE
			SYNTAX	INTEGER
			MAX-ACCESS	read-only
			STATUS	current
			::= { hmWanMbus29 43 }

hmWanMbus29VIF13		OBJECT-TYPE
			SYNTAX	INTEGER
			MAX-ACCESS	read-only
			STATUS	current
			::= { hmWanMbus29 44 }

hmWanMbus29Value13		OBJECT-TYPE
			SYNTAX	INTEGER
			MAX-ACCESS	read-only
			STATUS	current
			::= { hmWanMbus29 45 }

hmWanMbus29VIF14		OBJECT-TYPE
			SYNTAX	INTEGER
			MAX-ACCESS	read-only
			STATUS	current
			::= { hmWanMbus29 46 }

hmWanMbus29Value14		OBJECT-TYPE
			SYNTAX	INTEGER
			MAX-ACCESS	read-only
			STATUS	current
			::= { hmWanMbus29 47 }

hmWanMbus29VIF15		OBJECT-TYPE
			SYNTAX	INTEGER
			MAX-ACCESS	read-only
			STATUS	current
			::= { hmWanMbus29 48 }

hmWanMbus29Value15		OBJECT-TYPE
			SYNTAX	INTEGER
			MAX-ACCESS	read-only
			STATUS	current
			::= { hmWanMbus29 49 }

hmWanMbus29VIF16		OBJECT-TYPE
			SYNTAX	INTEGER
			MAX-ACCESS	read-only
			STATUS	current
			::= { hmWanMbus29 50 }

hmWanMbus29Value16		OBJECT-TYPE
			SYNTAX	INTEGER
			MAX-ACCESS	read-only
			STATUS	current
			::= { hmWanMbus29 51 }

hmWanMbus29VIF17		OBJECT-TYPE
			SYNTAX	INTEGER
			MAX-ACCESS	read-only
			STATUS	current
			::= { hmWanMbus29 52 }

hmWanMbus29Value17		OBJECT-TYPE
			SYNTAX	INTEGER
			MAX-ACCESS	read-only
			STATUS	current
			::= { hmWanMbus29 53 }

hmWanMbus29VIF18		OBJECT-TYPE
			SYNTAX	INTEGER
			MAX-ACCESS	read-only
			STATUS	current
			::= { hmWanMbus29 54 }

hmWanMbus29Value18		OBJECT-TYPE
			SYNTAX	INTEGER
			MAX-ACCESS	read-only
			STATUS	current
			::= { hmWanMbus29 55 }

hmWanMbus29VIF19		OBJECT-TYPE
			SYNTAX	INTEGER
			MAX-ACCESS	read-only
			STATUS	current
			::= { hmWanMbus29 56 }

hmWanMbus29Value19		OBJECT-TYPE
			SYNTAX	INTEGER
			MAX-ACCESS	read-only
			STATUS	current
			::= { hmWanMbus29 57 }

hmWanMbus29VIF1A		OBJECT-TYPE
			SYNTAX	INTEGER
			MAX-ACCESS	read-only
			STATUS	current
			::= { hmWanMbus29 58 }

hmWanMbus29Value1A		OBJECT-TYPE
			SYNTAX	INTEGER
			MAX-ACCESS	read-only
			STATUS	current
			::= { hmWanMbus29 59 }

hmWanMbus29VIF1B		OBJECT-TYPE
			SYNTAX	INTEGER
			MAX-ACCESS	read-only
			STATUS	current
			::= { hmWanMbus29 60 }

hmWanMbus29Value1B		OBJECT-TYPE
			SYNTAX	INTEGER
			MAX-ACCESS	read-only
			STATUS	current
			::= { hmWanMbus29 61 }

hmWanMbus29VIF1C		OBJECT-TYPE
			SYNTAX	INTEGER
			MAX-ACCESS	read-only
			STATUS	current
			::= { hmWanMbus29 62 }

hmWanMbus29Value1C		OBJECT-TYPE
			SYNTAX	INTEGER
			MAX-ACCESS	read-only
			STATUS	current
			::= { hmWanMbus29 63 }

hmWanMbus29VIF1D		OBJECT-TYPE
			SYNTAX	INTEGER
			MAX-ACCESS	read-only
			STATUS	current
			::= { hmWanMbus29 64 }

hmWanMbus29Value1D		OBJECT-TYPE
			SYNTAX	INTEGER
			MAX-ACCESS	read-only
			STATUS	current
			::= { hmWanMbus29 65 }

hmWanMbus29VIF1E		OBJECT-TYPE
			SYNTAX	INTEGER
			MAX-ACCESS	read-only
			STATUS	current
			::= { hmWanMbus29 66 }

hmWanMbus29Value1E		OBJECT-TYPE
			SYNTAX	INTEGER
			MAX-ACCESS	read-only
			STATUS	current
			::= { hmWanMbus29 67 }

hmWanMbus29VIF1F		OBJECT-TYPE
			SYNTAX	INTEGER
			MAX-ACCESS	read-only
			STATUS	current
			::= { hmWanMbus29 68 }

hmWanMbus29Value1F		OBJECT-TYPE
			SYNTAX	INTEGER
			MAX-ACCESS	read-only
			STATUS	current
			::= { hmWanMbus29 69 }

hmWanMbus29VIF20		OBJECT-TYPE
			SYNTAX	INTEGER
			MAX-ACCESS	read-only
			STATUS	current
			::= { hmWanMbus29 70 }

hmWanMbus29Value20		OBJECT-TYPE
			SYNTAX	INTEGER
			MAX-ACCESS	read-only
			STATUS	current
			::= { hmWanMbus29 71 }

hmWanMbus29VIF21		OBJECT-TYPE
			SYNTAX	INTEGER
			MAX-ACCESS	read-only
			STATUS	current
			::= { hmWanMbus29 72 }

hmWanMbus29Value21		OBJECT-TYPE
			SYNTAX	INTEGER
			MAX-ACCESS	read-only
			STATUS	current
			::= { hmWanMbus29 73 }

hmWanMbus29VIF22		OBJECT-TYPE
			SYNTAX	INTEGER
			MAX-ACCESS	read-only
			STATUS	current
			::= { hmWanMbus29 74 }

hmWanMbus29Value22		OBJECT-TYPE
			SYNTAX	INTEGER
			MAX-ACCESS	read-only
			STATUS	current
			::= { hmWanMbus29 75 }

hmWanMbus29VIF23		OBJECT-TYPE
			SYNTAX	INTEGER
			MAX-ACCESS	read-only
			STATUS	current
			::= { hmWanMbus29 76 }

hmWanMbus29Value23		OBJECT-TYPE
			SYNTAX	INTEGER
			MAX-ACCESS	read-only
			STATUS	current
			::= { hmWanMbus29 77 }

hmWanMbus29VIF24		OBJECT-TYPE
			SYNTAX	INTEGER
			MAX-ACCESS	read-only
			STATUS	current
			::= { hmWanMbus29 78 }

hmWanMbus29Value24		OBJECT-TYPE
			SYNTAX	INTEGER
			MAX-ACCESS	read-only
			STATUS	current
			::= { hmWanMbus29 79 }

hmWanMbus29VIF25		OBJECT-TYPE
			SYNTAX	INTEGER
			MAX-ACCESS	read-only
			STATUS	current
			::= { hmWanMbus29 80 }

hmWanMbus29Value25		OBJECT-TYPE
			SYNTAX	INTEGER
			MAX-ACCESS	read-only
			STATUS	current
			::= { hmWanMbus29 81 }

hmWanMbus29VIF26		OBJECT-TYPE
			SYNTAX	INTEGER
			MAX-ACCESS	read-only
			STATUS	current
			::= { hmWanMbus29 82 }

hmWanMbus29Value26		OBJECT-TYPE
			SYNTAX	INTEGER
			MAX-ACCESS	read-only
			STATUS	current
			::= { hmWanMbus29 83 }

hmWanMbus29VIF27		OBJECT-TYPE
			SYNTAX	INTEGER
			MAX-ACCESS	read-only
			STATUS	current
			::= { hmWanMbus29 84 }

hmWanMbus29Value27		OBJECT-TYPE
			SYNTAX	INTEGER
			MAX-ACCESS	read-only
			STATUS	current
			::= { hmWanMbus29 85 }

hmWanMbus29VIF28		OBJECT-TYPE
			SYNTAX	INTEGER
			MAX-ACCESS	read-only
			STATUS	current
			::= { hmWanMbus29 86 }

hmWanMbus29Value28		OBJECT-TYPE
			SYNTAX	INTEGER
			MAX-ACCESS	read-only
			STATUS	current
			::= { hmWanMbus29 87 }

hmWanMbus29VIF29		OBJECT-TYPE
			SYNTAX	INTEGER
			MAX-ACCESS	read-only
			STATUS	current
			::= { hmWanMbus29 88 }

hmWanMbus29Value29		OBJECT-TYPE
			SYNTAX	INTEGER
			MAX-ACCESS	read-only
			STATUS	current
			::= { hmWanMbus29 89 }

hmWanMbus29VIF2A		OBJECT-TYPE
			SYNTAX	INTEGER
			MAX-ACCESS	read-only
			STATUS	current
			::= { hmWanMbus29 90 }

hmWanMbus29Value2A		OBJECT-TYPE
			SYNTAX	INTEGER
			MAX-ACCESS	read-only
			STATUS	current
			::= { hmWanMbus29 91 }

hmWanMbus29VIF2B		OBJECT-TYPE
			SYNTAX	INTEGER
			MAX-ACCESS	read-only
			STATUS	current
			::= { hmWanMbus29 92 }

hmWanMbus29Value2B		OBJECT-TYPE
			SYNTAX	INTEGER
			MAX-ACCESS	read-only
			STATUS	current
			::= { hmWanMbus29 93 }

hmWanMbus29VIF2C		OBJECT-TYPE
			SYNTAX	INTEGER
			MAX-ACCESS	read-only
			STATUS	current
			::= { hmWanMbus29 94 }

hmWanMbus29Value2C		OBJECT-TYPE
			SYNTAX	INTEGER
			MAX-ACCESS	read-only
			STATUS	current
			::= { hmWanMbus29 95 }

hmWanMbus29VIF2D		OBJECT-TYPE
			SYNTAX	INTEGER
			MAX-ACCESS	read-only
			STATUS	current
			::= { hmWanMbus29 96 }

hmWanMbus29Value2D		OBJECT-TYPE
			SYNTAX	INTEGER
			MAX-ACCESS	read-only
			STATUS	current
			::= { hmWanMbus29 97 }

hmWanMbus29VIF2E		OBJECT-TYPE
			SYNTAX	INTEGER
			MAX-ACCESS	read-only
			STATUS	current
			::= { hmWanMbus29 98 }

hmWanMbus29Value2E		OBJECT-TYPE
			SYNTAX	INTEGER
			MAX-ACCESS	read-only
			STATUS	current
			::= { hmWanMbus29 99 }

hmWanMbus29VIF2F		OBJECT-TYPE
			SYNTAX	INTEGER
			MAX-ACCESS	read-only
			STATUS	current
			::= { hmWanMbus29 100 }

hmWanMbus29Value2F		OBJECT-TYPE
			SYNTAX	INTEGER
			MAX-ACCESS	read-only
			STATUS	current
			::= { hmWanMbus29 101 }

hmWanMbus2A			OBJECT IDENTIFIER ::= { hmWanMbus 42 }

hmWanMbus2AIdNumber		OBJECT-TYPE
			SYNTAX	Gauge32
			MAX-ACCESS	read-only
			STATUS	current
			::= { hmWanMbus2A 1 }

hmWanMbus2AManufacturer	OBJECT-TYPE
			SYNTAX	Gauge32
			MAX-ACCESS	read-only
			STATUS	current
			::= { hmWanMbus2A 2 }

hmWanMbus2AVersion		OBJECT-TYPE
			SYNTAX	Gauge32
			MAX-ACCESS	read-only
			STATUS	current
			::= { hmWanMbus2A 3 }

hmWanMbus2AMedium		OBJECT-TYPE
			SYNTAX	Gauge32
			MAX-ACCESS	read-only
			STATUS	current
			::= { hmWanMbus2A 4 }

hmWanMbus2AStatus		OBJECT-TYPE
			SYNTAX	Gauge32
			MAX-ACCESS	read-only
			STATUS	current
			::= { hmWanMbus2A 5 }

hmWanMbus2AVIF00		OBJECT-TYPE
			SYNTAX	INTEGER
			MAX-ACCESS	read-only
			STATUS	current
			::= { hmWanMbus2A 6 }

hmWanMbus2AValue00		OBJECT-TYPE
			SYNTAX	INTEGER
			MAX-ACCESS	read-only
			STATUS	current
			::= { hmWanMbus2A 7 }

hmWanMbus2AVIF01		OBJECT-TYPE
			SYNTAX	INTEGER
			MAX-ACCESS	read-only
			STATUS	current
			::= { hmWanMbus2A 8 }

hmWanMbus2AValue01		OBJECT-TYPE
			SYNTAX	INTEGER
			MAX-ACCESS	read-only
			STATUS	current
			::= { hmWanMbus2A 9 }

hmWanMbus2AVIF02		OBJECT-TYPE
			SYNTAX	INTEGER
			MAX-ACCESS	read-only
			STATUS	current
			::= { hmWanMbus2A 10 }

hmWanMbus2AValue02		OBJECT-TYPE
			SYNTAX	INTEGER
			MAX-ACCESS	read-only
			STATUS	current
			::= { hmWanMbus2A 11 }

hmWanMbus2AVIF03		OBJECT-TYPE
			SYNTAX	INTEGER
			MAX-ACCESS	read-only
			STATUS	current
			::= { hmWanMbus2A 12 }

hmWanMbus2AValue03		OBJECT-TYPE
			SYNTAX	INTEGER
			MAX-ACCESS	read-only
			STATUS	current
			::= { hmWanMbus2A 13 }

hmWanMbus2AVIF04		OBJECT-TYPE
			SYNTAX	INTEGER
			MAX-ACCESS	read-only
			STATUS	current
			::= { hmWanMbus2A 14 }

hmWanMbus2AValue04		OBJECT-TYPE
			SYNTAX	INTEGER
			MAX-ACCESS	read-only
			STATUS	current
			::= { hmWanMbus2A 15 }

hmWanMbus2AVIF05		OBJECT-TYPE
			SYNTAX	INTEGER
			MAX-ACCESS	read-only
			STATUS	current
			::= { hmWanMbus2A 16 }

hmWanMbus2AValue05		OBJECT-TYPE
			SYNTAX	INTEGER
			MAX-ACCESS	read-only
			STATUS	current
			::= { hmWanMbus2A 17 }

hmWanMbus2AVIF06		OBJECT-TYPE
			SYNTAX	INTEGER
			MAX-ACCESS	read-only
			STATUS	current
			::= { hmWanMbus2A 18 }

hmWanMbus2AValue06		OBJECT-TYPE
			SYNTAX	INTEGER
			MAX-ACCESS	read-only
			STATUS	current
			::= { hmWanMbus2A 19 }

hmWanMbus2AVIF07		OBJECT-TYPE
			SYNTAX	INTEGER
			MAX-ACCESS	read-only
			STATUS	current
			::= { hmWanMbus2A 20 }

hmWanMbus2AValue07		OBJECT-TYPE
			SYNTAX	INTEGER
			MAX-ACCESS	read-only
			STATUS	current
			::= { hmWanMbus2A 21 }

hmWanMbus2AVIF08		OBJECT-TYPE
			SYNTAX	INTEGER
			MAX-ACCESS	read-only
			STATUS	current
			::= { hmWanMbus2A 22 }

hmWanMbus2AValue08		OBJECT-TYPE
			SYNTAX	INTEGER
			MAX-ACCESS	read-only
			STATUS	current
			::= { hmWanMbus2A 23 }

hmWanMbus2AVIF09		OBJECT-TYPE
			SYNTAX	INTEGER
			MAX-ACCESS	read-only
			STATUS	current
			::= { hmWanMbus2A 24 }

hmWanMbus2AValue09		OBJECT-TYPE
			SYNTAX	INTEGER
			MAX-ACCESS	read-only
			STATUS	current
			::= { hmWanMbus2A 25 }

hmWanMbus2AVIF0A		OBJECT-TYPE
			SYNTAX	INTEGER
			MAX-ACCESS	read-only
			STATUS	current
			::= { hmWanMbus2A 26 }

hmWanMbus2AValue0A		OBJECT-TYPE
			SYNTAX	INTEGER
			MAX-ACCESS	read-only
			STATUS	current
			::= { hmWanMbus2A 27 }

hmWanMbus2AVIF0B		OBJECT-TYPE
			SYNTAX	INTEGER
			MAX-ACCESS	read-only
			STATUS	current
			::= { hmWanMbus2A 28 }

hmWanMbus2AValue0B		OBJECT-TYPE
			SYNTAX	INTEGER
			MAX-ACCESS	read-only
			STATUS	current
			::= { hmWanMbus2A 29 }

hmWanMbus2AVIF0C		OBJECT-TYPE
			SYNTAX	INTEGER
			MAX-ACCESS	read-only
			STATUS	current
			::= { hmWanMbus2A 30 }

hmWanMbus2AValue0C		OBJECT-TYPE
			SYNTAX	INTEGER
			MAX-ACCESS	read-only
			STATUS	current
			::= { hmWanMbus2A 31 }

hmWanMbus2AVIF0D		OBJECT-TYPE
			SYNTAX	INTEGER
			MAX-ACCESS	read-only
			STATUS	current
			::= { hmWanMbus2A 32 }

hmWanMbus2AValue0D		OBJECT-TYPE
			SYNTAX	INTEGER
			MAX-ACCESS	read-only
			STATUS	current
			::= { hmWanMbus2A 33 }

hmWanMbus2AVIF0E		OBJECT-TYPE
			SYNTAX	INTEGER
			MAX-ACCESS	read-only
			STATUS	current
			::= { hmWanMbus2A 34 }

hmWanMbus2AValue0E		OBJECT-TYPE
			SYNTAX	INTEGER
			MAX-ACCESS	read-only
			STATUS	current
			::= { hmWanMbus2A 35 }

hmWanMbus2AVIF0F		OBJECT-TYPE
			SYNTAX	INTEGER
			MAX-ACCESS	read-only
			STATUS	current
			::= { hmWanMbus2A 36 }

hmWanMbus2AValue0F		OBJECT-TYPE
			SYNTAX	INTEGER
			MAX-ACCESS	read-only
			STATUS	current
			::= { hmWanMbus2A 37 }

hmWanMbus2AVIF10		OBJECT-TYPE
			SYNTAX	INTEGER
			MAX-ACCESS	read-only
			STATUS	current
			::= { hmWanMbus2A 38 }

hmWanMbus2AValue10		OBJECT-TYPE
			SYNTAX	INTEGER
			MAX-ACCESS	read-only
			STATUS	current
			::= { hmWanMbus2A 39 }

hmWanMbus2AVIF11		OBJECT-TYPE
			SYNTAX	INTEGER
			MAX-ACCESS	read-only
			STATUS	current
			::= { hmWanMbus2A 40 }

hmWanMbus2AValue11		OBJECT-TYPE
			SYNTAX	INTEGER
			MAX-ACCESS	read-only
			STATUS	current
			::= { hmWanMbus2A 41 }

hmWanMbus2AVIF12		OBJECT-TYPE
			SYNTAX	INTEGER
			MAX-ACCESS	read-only
			STATUS	current
			::= { hmWanMbus2A 42 }

hmWanMbus2AValue12		OBJECT-TYPE
			SYNTAX	INTEGER
			MAX-ACCESS	read-only
			STATUS	current
			::= { hmWanMbus2A 43 }

hmWanMbus2AVIF13		OBJECT-TYPE
			SYNTAX	INTEGER
			MAX-ACCESS	read-only
			STATUS	current
			::= { hmWanMbus2A 44 }

hmWanMbus2AValue13		OBJECT-TYPE
			SYNTAX	INTEGER
			MAX-ACCESS	read-only
			STATUS	current
			::= { hmWanMbus2A 45 }

hmWanMbus2AVIF14		OBJECT-TYPE
			SYNTAX	INTEGER
			MAX-ACCESS	read-only
			STATUS	current
			::= { hmWanMbus2A 46 }

hmWanMbus2AValue14		OBJECT-TYPE
			SYNTAX	INTEGER
			MAX-ACCESS	read-only
			STATUS	current
			::= { hmWanMbus2A 47 }

hmWanMbus2AVIF15		OBJECT-TYPE
			SYNTAX	INTEGER
			MAX-ACCESS	read-only
			STATUS	current
			::= { hmWanMbus2A 48 }

hmWanMbus2AValue15		OBJECT-TYPE
			SYNTAX	INTEGER
			MAX-ACCESS	read-only
			STATUS	current
			::= { hmWanMbus2A 49 }

hmWanMbus2AVIF16		OBJECT-TYPE
			SYNTAX	INTEGER
			MAX-ACCESS	read-only
			STATUS	current
			::= { hmWanMbus2A 50 }

hmWanMbus2AValue16		OBJECT-TYPE
			SYNTAX	INTEGER
			MAX-ACCESS	read-only
			STATUS	current
			::= { hmWanMbus2A 51 }

hmWanMbus2AVIF17		OBJECT-TYPE
			SYNTAX	INTEGER
			MAX-ACCESS	read-only
			STATUS	current
			::= { hmWanMbus2A 52 }

hmWanMbus2AValue17		OBJECT-TYPE
			SYNTAX	INTEGER
			MAX-ACCESS	read-only
			STATUS	current
			::= { hmWanMbus2A 53 }

hmWanMbus2AVIF18		OBJECT-TYPE
			SYNTAX	INTEGER
			MAX-ACCESS	read-only
			STATUS	current
			::= { hmWanMbus2A 54 }

hmWanMbus2AValue18		OBJECT-TYPE
			SYNTAX	INTEGER
			MAX-ACCESS	read-only
			STATUS	current
			::= { hmWanMbus2A 55 }

hmWanMbus2AVIF19		OBJECT-TYPE
			SYNTAX	INTEGER
			MAX-ACCESS	read-only
			STATUS	current
			::= { hmWanMbus2A 56 }

hmWanMbus2AValue19		OBJECT-TYPE
			SYNTAX	INTEGER
			MAX-ACCESS	read-only
			STATUS	current
			::= { hmWanMbus2A 57 }

hmWanMbus2AVIF1A		OBJECT-TYPE
			SYNTAX	INTEGER
			MAX-ACCESS	read-only
			STATUS	current
			::= { hmWanMbus2A 58 }

hmWanMbus2AValue1A		OBJECT-TYPE
			SYNTAX	INTEGER
			MAX-ACCESS	read-only
			STATUS	current
			::= { hmWanMbus2A 59 }

hmWanMbus2AVIF1B		OBJECT-TYPE
			SYNTAX	INTEGER
			MAX-ACCESS	read-only
			STATUS	current
			::= { hmWanMbus2A 60 }

hmWanMbus2AValue1B		OBJECT-TYPE
			SYNTAX	INTEGER
			MAX-ACCESS	read-only
			STATUS	current
			::= { hmWanMbus2A 61 }

hmWanMbus2AVIF1C		OBJECT-TYPE
			SYNTAX	INTEGER
			MAX-ACCESS	read-only
			STATUS	current
			::= { hmWanMbus2A 62 }

hmWanMbus2AValue1C		OBJECT-TYPE
			SYNTAX	INTEGER
			MAX-ACCESS	read-only
			STATUS	current
			::= { hmWanMbus2A 63 }

hmWanMbus2AVIF1D		OBJECT-TYPE
			SYNTAX	INTEGER
			MAX-ACCESS	read-only
			STATUS	current
			::= { hmWanMbus2A 64 }

hmWanMbus2AValue1D		OBJECT-TYPE
			SYNTAX	INTEGER
			MAX-ACCESS	read-only
			STATUS	current
			::= { hmWanMbus2A 65 }

hmWanMbus2AVIF1E		OBJECT-TYPE
			SYNTAX	INTEGER
			MAX-ACCESS	read-only
			STATUS	current
			::= { hmWanMbus2A 66 }

hmWanMbus2AValue1E		OBJECT-TYPE
			SYNTAX	INTEGER
			MAX-ACCESS	read-only
			STATUS	current
			::= { hmWanMbus2A 67 }

hmWanMbus2AVIF1F		OBJECT-TYPE
			SYNTAX	INTEGER
			MAX-ACCESS	read-only
			STATUS	current
			::= { hmWanMbus2A 68 }

hmWanMbus2AValue1F		OBJECT-TYPE
			SYNTAX	INTEGER
			MAX-ACCESS	read-only
			STATUS	current
			::= { hmWanMbus2A 69 }

hmWanMbus2AVIF20		OBJECT-TYPE
			SYNTAX	INTEGER
			MAX-ACCESS	read-only
			STATUS	current
			::= { hmWanMbus2A 70 }

hmWanMbus2AValue20		OBJECT-TYPE
			SYNTAX	INTEGER
			MAX-ACCESS	read-only
			STATUS	current
			::= { hmWanMbus2A 71 }

hmWanMbus2AVIF21		OBJECT-TYPE
			SYNTAX	INTEGER
			MAX-ACCESS	read-only
			STATUS	current
			::= { hmWanMbus2A 72 }

hmWanMbus2AValue21		OBJECT-TYPE
			SYNTAX	INTEGER
			MAX-ACCESS	read-only
			STATUS	current
			::= { hmWanMbus2A 73 }

hmWanMbus2AVIF22		OBJECT-TYPE
			SYNTAX	INTEGER
			MAX-ACCESS	read-only
			STATUS	current
			::= { hmWanMbus2A 74 }

hmWanMbus2AValue22		OBJECT-TYPE
			SYNTAX	INTEGER
			MAX-ACCESS	read-only
			STATUS	current
			::= { hmWanMbus2A 75 }

hmWanMbus2AVIF23		OBJECT-TYPE
			SYNTAX	INTEGER
			MAX-ACCESS	read-only
			STATUS	current
			::= { hmWanMbus2A 76 }

hmWanMbus2AValue23		OBJECT-TYPE
			SYNTAX	INTEGER
			MAX-ACCESS	read-only
			STATUS	current
			::= { hmWanMbus2A 77 }

hmWanMbus2AVIF24		OBJECT-TYPE
			SYNTAX	INTEGER
			MAX-ACCESS	read-only
			STATUS	current
			::= { hmWanMbus2A 78 }

hmWanMbus2AValue24		OBJECT-TYPE
			SYNTAX	INTEGER
			MAX-ACCESS	read-only
			STATUS	current
			::= { hmWanMbus2A 79 }

hmWanMbus2AVIF25		OBJECT-TYPE
			SYNTAX	INTEGER
			MAX-ACCESS	read-only
			STATUS	current
			::= { hmWanMbus2A 80 }

hmWanMbus2AValue25		OBJECT-TYPE
			SYNTAX	INTEGER
			MAX-ACCESS	read-only
			STATUS	current
			::= { hmWanMbus2A 81 }

hmWanMbus2AVIF26		OBJECT-TYPE
			SYNTAX	INTEGER
			MAX-ACCESS	read-only
			STATUS	current
			::= { hmWanMbus2A 82 }

hmWanMbus2AValue26		OBJECT-TYPE
			SYNTAX	INTEGER
			MAX-ACCESS	read-only
			STATUS	current
			::= { hmWanMbus2A 83 }

hmWanMbus2AVIF27		OBJECT-TYPE
			SYNTAX	INTEGER
			MAX-ACCESS	read-only
			STATUS	current
			::= { hmWanMbus2A 84 }

hmWanMbus2AValue27		OBJECT-TYPE
			SYNTAX	INTEGER
			MAX-ACCESS	read-only
			STATUS	current
			::= { hmWanMbus2A 85 }

hmWanMbus2AVIF28		OBJECT-TYPE
			SYNTAX	INTEGER
			MAX-ACCESS	read-only
			STATUS	current
			::= { hmWanMbus2A 86 }

hmWanMbus2AValue28		OBJECT-TYPE
			SYNTAX	INTEGER
			MAX-ACCESS	read-only
			STATUS	current
			::= { hmWanMbus2A 87 }

hmWanMbus2AVIF29		OBJECT-TYPE
			SYNTAX	INTEGER
			MAX-ACCESS	read-only
			STATUS	current
			::= { hmWanMbus2A 88 }

hmWanMbus2AValue29		OBJECT-TYPE
			SYNTAX	INTEGER
			MAX-ACCESS	read-only
			STATUS	current
			::= { hmWanMbus2A 89 }

hmWanMbus2AVIF2A		OBJECT-TYPE
			SYNTAX	INTEGER
			MAX-ACCESS	read-only
			STATUS	current
			::= { hmWanMbus2A 90 }

hmWanMbus2AValue2A		OBJECT-TYPE
			SYNTAX	INTEGER
			MAX-ACCESS	read-only
			STATUS	current
			::= { hmWanMbus2A 91 }

hmWanMbus2AVIF2B		OBJECT-TYPE
			SYNTAX	INTEGER
			MAX-ACCESS	read-only
			STATUS	current
			::= { hmWanMbus2A 92 }

hmWanMbus2AValue2B		OBJECT-TYPE
			SYNTAX	INTEGER
			MAX-ACCESS	read-only
			STATUS	current
			::= { hmWanMbus2A 93 }

hmWanMbus2AVIF2C		OBJECT-TYPE
			SYNTAX	INTEGER
			MAX-ACCESS	read-only
			STATUS	current
			::= { hmWanMbus2A 94 }

hmWanMbus2AValue2C		OBJECT-TYPE
			SYNTAX	INTEGER
			MAX-ACCESS	read-only
			STATUS	current
			::= { hmWanMbus2A 95 }

hmWanMbus2AVIF2D		OBJECT-TYPE
			SYNTAX	INTEGER
			MAX-ACCESS	read-only
			STATUS	current
			::= { hmWanMbus2A 96 }

hmWanMbus2AValue2D		OBJECT-TYPE
			SYNTAX	INTEGER
			MAX-ACCESS	read-only
			STATUS	current
			::= { hmWanMbus2A 97 }

hmWanMbus2AVIF2E		OBJECT-TYPE
			SYNTAX	INTEGER
			MAX-ACCESS	read-only
			STATUS	current
			::= { hmWanMbus2A 98 }

hmWanMbus2AValue2E		OBJECT-TYPE
			SYNTAX	INTEGER
			MAX-ACCESS	read-only
			STATUS	current
			::= { hmWanMbus2A 99 }

hmWanMbus2AVIF2F		OBJECT-TYPE
			SYNTAX	INTEGER
			MAX-ACCESS	read-only
			STATUS	current
			::= { hmWanMbus2A 100 }

hmWanMbus2AValue2F		OBJECT-TYPE
			SYNTAX	INTEGER
			MAX-ACCESS	read-only
			STATUS	current
			::= { hmWanMbus2A 101 }

hmWanMbus2B			OBJECT IDENTIFIER ::= { hmWanMbus 43 }

hmWanMbus2BIdNumber		OBJECT-TYPE
			SYNTAX	Gauge32
			MAX-ACCESS	read-only
			STATUS	current
			::= { hmWanMbus2B 1 }

hmWanMbus2BManufacturer	OBJECT-TYPE
			SYNTAX	Gauge32
			MAX-ACCESS	read-only
			STATUS	current
			::= { hmWanMbus2B 2 }

hmWanMbus2BVersion		OBJECT-TYPE
			SYNTAX	Gauge32
			MAX-ACCESS	read-only
			STATUS	current
			::= { hmWanMbus2B 3 }

hmWanMbus2BMedium		OBJECT-TYPE
			SYNTAX	Gauge32
			MAX-ACCESS	read-only
			STATUS	current
			::= { hmWanMbus2B 4 }

hmWanMbus2BStatus		OBJECT-TYPE
			SYNTAX	Gauge32
			MAX-ACCESS	read-only
			STATUS	current
			::= { hmWanMbus2B 5 }

hmWanMbus2BVIF00		OBJECT-TYPE
			SYNTAX	INTEGER
			MAX-ACCESS	read-only
			STATUS	current
			::= { hmWanMbus2B 6 }

hmWanMbus2BValue00		OBJECT-TYPE
			SYNTAX	INTEGER
			MAX-ACCESS	read-only
			STATUS	current
			::= { hmWanMbus2B 7 }

hmWanMbus2BVIF01		OBJECT-TYPE
			SYNTAX	INTEGER
			MAX-ACCESS	read-only
			STATUS	current
			::= { hmWanMbus2B 8 }

hmWanMbus2BValue01		OBJECT-TYPE
			SYNTAX	INTEGER
			MAX-ACCESS	read-only
			STATUS	current
			::= { hmWanMbus2B 9 }

hmWanMbus2BVIF02		OBJECT-TYPE
			SYNTAX	INTEGER
			MAX-ACCESS	read-only
			STATUS	current
			::= { hmWanMbus2B 10 }

hmWanMbus2BValue02		OBJECT-TYPE
			SYNTAX	INTEGER
			MAX-ACCESS	read-only
			STATUS	current
			::= { hmWanMbus2B 11 }

hmWanMbus2BVIF03		OBJECT-TYPE
			SYNTAX	INTEGER
			MAX-ACCESS	read-only
			STATUS	current
			::= { hmWanMbus2B 12 }

hmWanMbus2BValue03		OBJECT-TYPE
			SYNTAX	INTEGER
			MAX-ACCESS	read-only
			STATUS	current
			::= { hmWanMbus2B 13 }

hmWanMbus2BVIF04		OBJECT-TYPE
			SYNTAX	INTEGER
			MAX-ACCESS	read-only
			STATUS	current
			::= { hmWanMbus2B 14 }

hmWanMbus2BValue04		OBJECT-TYPE
			SYNTAX	INTEGER
			MAX-ACCESS	read-only
			STATUS	current
			::= { hmWanMbus2B 15 }

hmWanMbus2BVIF05		OBJECT-TYPE
			SYNTAX	INTEGER
			MAX-ACCESS	read-only
			STATUS	current
			::= { hmWanMbus2B 16 }

hmWanMbus2BValue05		OBJECT-TYPE
			SYNTAX	INTEGER
			MAX-ACCESS	read-only
			STATUS	current
			::= { hmWanMbus2B 17 }

hmWanMbus2BVIF06		OBJECT-TYPE
			SYNTAX	INTEGER
			MAX-ACCESS	read-only
			STATUS	current
			::= { hmWanMbus2B 18 }

hmWanMbus2BValue06		OBJECT-TYPE
			SYNTAX	INTEGER
			MAX-ACCESS	read-only
			STATUS	current
			::= { hmWanMbus2B 19 }

hmWanMbus2BVIF07		OBJECT-TYPE
			SYNTAX	INTEGER
			MAX-ACCESS	read-only
			STATUS	current
			::= { hmWanMbus2B 20 }

hmWanMbus2BValue07		OBJECT-TYPE
			SYNTAX	INTEGER
			MAX-ACCESS	read-only
			STATUS	current
			::= { hmWanMbus2B 21 }

hmWanMbus2BVIF08		OBJECT-TYPE
			SYNTAX	INTEGER
			MAX-ACCESS	read-only
			STATUS	current
			::= { hmWanMbus2B 22 }

hmWanMbus2BValue08		OBJECT-TYPE
			SYNTAX	INTEGER
			MAX-ACCESS	read-only
			STATUS	current
			::= { hmWanMbus2B 23 }

hmWanMbus2BVIF09		OBJECT-TYPE
			SYNTAX	INTEGER
			MAX-ACCESS	read-only
			STATUS	current
			::= { hmWanMbus2B 24 }

hmWanMbus2BValue09		OBJECT-TYPE
			SYNTAX	INTEGER
			MAX-ACCESS	read-only
			STATUS	current
			::= { hmWanMbus2B 25 }

hmWanMbus2BVIF0A		OBJECT-TYPE
			SYNTAX	INTEGER
			MAX-ACCESS	read-only
			STATUS	current
			::= { hmWanMbus2B 26 }

hmWanMbus2BValue0A		OBJECT-TYPE
			SYNTAX	INTEGER
			MAX-ACCESS	read-only
			STATUS	current
			::= { hmWanMbus2B 27 }

hmWanMbus2BVIF0B		OBJECT-TYPE
			SYNTAX	INTEGER
			MAX-ACCESS	read-only
			STATUS	current
			::= { hmWanMbus2B 28 }

hmWanMbus2BValue0B		OBJECT-TYPE
			SYNTAX	INTEGER
			MAX-ACCESS	read-only
			STATUS	current
			::= { hmWanMbus2B 29 }

hmWanMbus2BVIF0C		OBJECT-TYPE
			SYNTAX	INTEGER
			MAX-ACCESS	read-only
			STATUS	current
			::= { hmWanMbus2B 30 }

hmWanMbus2BValue0C		OBJECT-TYPE
			SYNTAX	INTEGER
			MAX-ACCESS	read-only
			STATUS	current
			::= { hmWanMbus2B 31 }

hmWanMbus2BVIF0D		OBJECT-TYPE
			SYNTAX	INTEGER
			MAX-ACCESS	read-only
			STATUS	current
			::= { hmWanMbus2B 32 }

hmWanMbus2BValue0D		OBJECT-TYPE
			SYNTAX	INTEGER
			MAX-ACCESS	read-only
			STATUS	current
			::= { hmWanMbus2B 33 }

hmWanMbus2BVIF0E		OBJECT-TYPE
			SYNTAX	INTEGER
			MAX-ACCESS	read-only
			STATUS	current
			::= { hmWanMbus2B 34 }

hmWanMbus2BValue0E		OBJECT-TYPE
			SYNTAX	INTEGER
			MAX-ACCESS	read-only
			STATUS	current
			::= { hmWanMbus2B 35 }

hmWanMbus2BVIF0F		OBJECT-TYPE
			SYNTAX	INTEGER
			MAX-ACCESS	read-only
			STATUS	current
			::= { hmWanMbus2B 36 }

hmWanMbus2BValue0F		OBJECT-TYPE
			SYNTAX	INTEGER
			MAX-ACCESS	read-only
			STATUS	current
			::= { hmWanMbus2B 37 }

hmWanMbus2BVIF10		OBJECT-TYPE
			SYNTAX	INTEGER
			MAX-ACCESS	read-only
			STATUS	current
			::= { hmWanMbus2B 38 }

hmWanMbus2BValue10		OBJECT-TYPE
			SYNTAX	INTEGER
			MAX-ACCESS	read-only
			STATUS	current
			::= { hmWanMbus2B 39 }

hmWanMbus2BVIF11		OBJECT-TYPE
			SYNTAX	INTEGER
			MAX-ACCESS	read-only
			STATUS	current
			::= { hmWanMbus2B 40 }

hmWanMbus2BValue11		OBJECT-TYPE
			SYNTAX	INTEGER
			MAX-ACCESS	read-only
			STATUS	current
			::= { hmWanMbus2B 41 }

hmWanMbus2BVIF12		OBJECT-TYPE
			SYNTAX	INTEGER
			MAX-ACCESS	read-only
			STATUS	current
			::= { hmWanMbus2B 42 }

hmWanMbus2BValue12		OBJECT-TYPE
			SYNTAX	INTEGER
			MAX-ACCESS	read-only
			STATUS	current
			::= { hmWanMbus2B 43 }

hmWanMbus2BVIF13		OBJECT-TYPE
			SYNTAX	INTEGER
			MAX-ACCESS	read-only
			STATUS	current
			::= { hmWanMbus2B 44 }

hmWanMbus2BValue13		OBJECT-TYPE
			SYNTAX	INTEGER
			MAX-ACCESS	read-only
			STATUS	current
			::= { hmWanMbus2B 45 }

hmWanMbus2BVIF14		OBJECT-TYPE
			SYNTAX	INTEGER
			MAX-ACCESS	read-only
			STATUS	current
			::= { hmWanMbus2B 46 }

hmWanMbus2BValue14		OBJECT-TYPE
			SYNTAX	INTEGER
			MAX-ACCESS	read-only
			STATUS	current
			::= { hmWanMbus2B 47 }

hmWanMbus2BVIF15		OBJECT-TYPE
			SYNTAX	INTEGER
			MAX-ACCESS	read-only
			STATUS	current
			::= { hmWanMbus2B 48 }

hmWanMbus2BValue15		OBJECT-TYPE
			SYNTAX	INTEGER
			MAX-ACCESS	read-only
			STATUS	current
			::= { hmWanMbus2B 49 }

hmWanMbus2BVIF16		OBJECT-TYPE
			SYNTAX	INTEGER
			MAX-ACCESS	read-only
			STATUS	current
			::= { hmWanMbus2B 50 }

hmWanMbus2BValue16		OBJECT-TYPE
			SYNTAX	INTEGER
			MAX-ACCESS	read-only
			STATUS	current
			::= { hmWanMbus2B 51 }

hmWanMbus2BVIF17		OBJECT-TYPE
			SYNTAX	INTEGER
			MAX-ACCESS	read-only
			STATUS	current
			::= { hmWanMbus2B 52 }

hmWanMbus2BValue17		OBJECT-TYPE
			SYNTAX	INTEGER
			MAX-ACCESS	read-only
			STATUS	current
			::= { hmWanMbus2B 53 }

hmWanMbus2BVIF18		OBJECT-TYPE
			SYNTAX	INTEGER
			MAX-ACCESS	read-only
			STATUS	current
			::= { hmWanMbus2B 54 }

hmWanMbus2BValue18		OBJECT-TYPE
			SYNTAX	INTEGER
			MAX-ACCESS	read-only
			STATUS	current
			::= { hmWanMbus2B 55 }

hmWanMbus2BVIF19		OBJECT-TYPE
			SYNTAX	INTEGER
			MAX-ACCESS	read-only
			STATUS	current
			::= { hmWanMbus2B 56 }

hmWanMbus2BValue19		OBJECT-TYPE
			SYNTAX	INTEGER
			MAX-ACCESS	read-only
			STATUS	current
			::= { hmWanMbus2B 57 }

hmWanMbus2BVIF1A		OBJECT-TYPE
			SYNTAX	INTEGER
			MAX-ACCESS	read-only
			STATUS	current
			::= { hmWanMbus2B 58 }

hmWanMbus2BValue1A		OBJECT-TYPE
			SYNTAX	INTEGER
			MAX-ACCESS	read-only
			STATUS	current
			::= { hmWanMbus2B 59 }

hmWanMbus2BVIF1B		OBJECT-TYPE
			SYNTAX	INTEGER
			MAX-ACCESS	read-only
			STATUS	current
			::= { hmWanMbus2B 60 }

hmWanMbus2BValue1B		OBJECT-TYPE
			SYNTAX	INTEGER
			MAX-ACCESS	read-only
			STATUS	current
			::= { hmWanMbus2B 61 }

hmWanMbus2BVIF1C		OBJECT-TYPE
			SYNTAX	INTEGER
			MAX-ACCESS	read-only
			STATUS	current
			::= { hmWanMbus2B 62 }

hmWanMbus2BValue1C		OBJECT-TYPE
			SYNTAX	INTEGER
			MAX-ACCESS	read-only
			STATUS	current
			::= { hmWanMbus2B 63 }

hmWanMbus2BVIF1D		OBJECT-TYPE
			SYNTAX	INTEGER
			MAX-ACCESS	read-only
			STATUS	current
			::= { hmWanMbus2B 64 }

hmWanMbus2BValue1D		OBJECT-TYPE
			SYNTAX	INTEGER
			MAX-ACCESS	read-only
			STATUS	current
			::= { hmWanMbus2B 65 }

hmWanMbus2BVIF1E		OBJECT-TYPE
			SYNTAX	INTEGER
			MAX-ACCESS	read-only
			STATUS	current
			::= { hmWanMbus2B 66 }

hmWanMbus2BValue1E		OBJECT-TYPE
			SYNTAX	INTEGER
			MAX-ACCESS	read-only
			STATUS	current
			::= { hmWanMbus2B 67 }

hmWanMbus2BVIF1F		OBJECT-TYPE
			SYNTAX	INTEGER
			MAX-ACCESS	read-only
			STATUS	current
			::= { hmWanMbus2B 68 }

hmWanMbus2BValue1F		OBJECT-TYPE
			SYNTAX	INTEGER
			MAX-ACCESS	read-only
			STATUS	current
			::= { hmWanMbus2B 69 }

hmWanMbus2BVIF20		OBJECT-TYPE
			SYNTAX	INTEGER
			MAX-ACCESS	read-only
			STATUS	current
			::= { hmWanMbus2B 70 }

hmWanMbus2BValue20		OBJECT-TYPE
			SYNTAX	INTEGER
			MAX-ACCESS	read-only
			STATUS	current
			::= { hmWanMbus2B 71 }

hmWanMbus2BVIF21		OBJECT-TYPE
			SYNTAX	INTEGER
			MAX-ACCESS	read-only
			STATUS	current
			::= { hmWanMbus2B 72 }

hmWanMbus2BValue21		OBJECT-TYPE
			SYNTAX	INTEGER
			MAX-ACCESS	read-only
			STATUS	current
			::= { hmWanMbus2B 73 }

hmWanMbus2BVIF22		OBJECT-TYPE
			SYNTAX	INTEGER
			MAX-ACCESS	read-only
			STATUS	current
			::= { hmWanMbus2B 74 }

hmWanMbus2BValue22		OBJECT-TYPE
			SYNTAX	INTEGER
			MAX-ACCESS	read-only
			STATUS	current
			::= { hmWanMbus2B 75 }

hmWanMbus2BVIF23		OBJECT-TYPE
			SYNTAX	INTEGER
			MAX-ACCESS	read-only
			STATUS	current
			::= { hmWanMbus2B 76 }

hmWanMbus2BValue23		OBJECT-TYPE
			SYNTAX	INTEGER
			MAX-ACCESS	read-only
			STATUS	current
			::= { hmWanMbus2B 77 }

hmWanMbus2BVIF24		OBJECT-TYPE
			SYNTAX	INTEGER
			MAX-ACCESS	read-only
			STATUS	current
			::= { hmWanMbus2B 78 }

hmWanMbus2BValue24		OBJECT-TYPE
			SYNTAX	INTEGER
			MAX-ACCESS	read-only
			STATUS	current
			::= { hmWanMbus2B 79 }

hmWanMbus2BVIF25		OBJECT-TYPE
			SYNTAX	INTEGER
			MAX-ACCESS	read-only
			STATUS	current
			::= { hmWanMbus2B 80 }

hmWanMbus2BValue25		OBJECT-TYPE
			SYNTAX	INTEGER
			MAX-ACCESS	read-only
			STATUS	current
			::= { hmWanMbus2B 81 }

hmWanMbus2BVIF26		OBJECT-TYPE
			SYNTAX	INTEGER
			MAX-ACCESS	read-only
			STATUS	current
			::= { hmWanMbus2B 82 }

hmWanMbus2BValue26		OBJECT-TYPE
			SYNTAX	INTEGER
			MAX-ACCESS	read-only
			STATUS	current
			::= { hmWanMbus2B 83 }

hmWanMbus2BVIF27		OBJECT-TYPE
			SYNTAX	INTEGER
			MAX-ACCESS	read-only
			STATUS	current
			::= { hmWanMbus2B 84 }

hmWanMbus2BValue27		OBJECT-TYPE
			SYNTAX	INTEGER
			MAX-ACCESS	read-only
			STATUS	current
			::= { hmWanMbus2B 85 }

hmWanMbus2BVIF28		OBJECT-TYPE
			SYNTAX	INTEGER
			MAX-ACCESS	read-only
			STATUS	current
			::= { hmWanMbus2B 86 }

hmWanMbus2BValue28		OBJECT-TYPE
			SYNTAX	INTEGER
			MAX-ACCESS	read-only
			STATUS	current
			::= { hmWanMbus2B 87 }

hmWanMbus2BVIF29		OBJECT-TYPE
			SYNTAX	INTEGER
			MAX-ACCESS	read-only
			STATUS	current
			::= { hmWanMbus2B 88 }

hmWanMbus2BValue29		OBJECT-TYPE
			SYNTAX	INTEGER
			MAX-ACCESS	read-only
			STATUS	current
			::= { hmWanMbus2B 89 }

hmWanMbus2BVIF2A		OBJECT-TYPE
			SYNTAX	INTEGER
			MAX-ACCESS	read-only
			STATUS	current
			::= { hmWanMbus2B 90 }

hmWanMbus2BValue2A		OBJECT-TYPE
			SYNTAX	INTEGER
			MAX-ACCESS	read-only
			STATUS	current
			::= { hmWanMbus2B 91 }

hmWanMbus2BVIF2B		OBJECT-TYPE
			SYNTAX	INTEGER
			MAX-ACCESS	read-only
			STATUS	current
			::= { hmWanMbus2B 92 }

hmWanMbus2BValue2B		OBJECT-TYPE
			SYNTAX	INTEGER
			MAX-ACCESS	read-only
			STATUS	current
			::= { hmWanMbus2B 93 }

hmWanMbus2BVIF2C		OBJECT-TYPE
			SYNTAX	INTEGER
			MAX-ACCESS	read-only
			STATUS	current
			::= { hmWanMbus2B 94 }

hmWanMbus2BValue2C		OBJECT-TYPE
			SYNTAX	INTEGER
			MAX-ACCESS	read-only
			STATUS	current
			::= { hmWanMbus2B 95 }

hmWanMbus2BVIF2D		OBJECT-TYPE
			SYNTAX	INTEGER
			MAX-ACCESS	read-only
			STATUS	current
			::= { hmWanMbus2B 96 }

hmWanMbus2BValue2D		OBJECT-TYPE
			SYNTAX	INTEGER
			MAX-ACCESS	read-only
			STATUS	current
			::= { hmWanMbus2B 97 }

hmWanMbus2BVIF2E		OBJECT-TYPE
			SYNTAX	INTEGER
			MAX-ACCESS	read-only
			STATUS	current
			::= { hmWanMbus2B 98 }

hmWanMbus2BValue2E		OBJECT-TYPE
			SYNTAX	INTEGER
			MAX-ACCESS	read-only
			STATUS	current
			::= { hmWanMbus2B 99 }

hmWanMbus2BVIF2F		OBJECT-TYPE
			SYNTAX	INTEGER
			MAX-ACCESS	read-only
			STATUS	current
			::= { hmWanMbus2B 100 }

hmWanMbus2BValue2F		OBJECT-TYPE
			SYNTAX	INTEGER
			MAX-ACCESS	read-only
			STATUS	current
			::= { hmWanMbus2B 101 }

hmWanMbus2C			OBJECT IDENTIFIER ::= { hmWanMbus 44 }

hmWanMbus2CIdNumber		OBJECT-TYPE
			SYNTAX	Gauge32
			MAX-ACCESS	read-only
			STATUS	current
			::= { hmWanMbus2C 1 }

hmWanMbus2CManufacturer	OBJECT-TYPE
			SYNTAX	Gauge32
			MAX-ACCESS	read-only
			STATUS	current
			::= { hmWanMbus2C 2 }

hmWanMbus2CVersion		OBJECT-TYPE
			SYNTAX	Gauge32
			MAX-ACCESS	read-only
			STATUS	current
			::= { hmWanMbus2C 3 }

hmWanMbus2CMedium		OBJECT-TYPE
			SYNTAX	Gauge32
			MAX-ACCESS	read-only
			STATUS	current
			::= { hmWanMbus2C 4 }

hmWanMbus2CStatus		OBJECT-TYPE
			SYNTAX	Gauge32
			MAX-ACCESS	read-only
			STATUS	current
			::= { hmWanMbus2C 5 }

hmWanMbus2CVIF00		OBJECT-TYPE
			SYNTAX	INTEGER
			MAX-ACCESS	read-only
			STATUS	current
			::= { hmWanMbus2C 6 }

hmWanMbus2CValue00		OBJECT-TYPE
			SYNTAX	INTEGER
			MAX-ACCESS	read-only
			STATUS	current
			::= { hmWanMbus2C 7 }

hmWanMbus2CVIF01		OBJECT-TYPE
			SYNTAX	INTEGER
			MAX-ACCESS	read-only
			STATUS	current
			::= { hmWanMbus2C 8 }

hmWanMbus2CValue01		OBJECT-TYPE
			SYNTAX	INTEGER
			MAX-ACCESS	read-only
			STATUS	current
			::= { hmWanMbus2C 9 }

hmWanMbus2CVIF02		OBJECT-TYPE
			SYNTAX	INTEGER
			MAX-ACCESS	read-only
			STATUS	current
			::= { hmWanMbus2C 10 }

hmWanMbus2CValue02		OBJECT-TYPE
			SYNTAX	INTEGER
			MAX-ACCESS	read-only
			STATUS	current
			::= { hmWanMbus2C 11 }

hmWanMbus2CVIF03		OBJECT-TYPE
			SYNTAX	INTEGER
			MAX-ACCESS	read-only
			STATUS	current
			::= { hmWanMbus2C 12 }

hmWanMbus2CValue03		OBJECT-TYPE
			SYNTAX	INTEGER
			MAX-ACCESS	read-only
			STATUS	current
			::= { hmWanMbus2C 13 }

hmWanMbus2CVIF04		OBJECT-TYPE
			SYNTAX	INTEGER
			MAX-ACCESS	read-only
			STATUS	current
			::= { hmWanMbus2C 14 }

hmWanMbus2CValue04		OBJECT-TYPE
			SYNTAX	INTEGER
			MAX-ACCESS	read-only
			STATUS	current
			::= { hmWanMbus2C 15 }

hmWanMbus2CVIF05		OBJECT-TYPE
			SYNTAX	INTEGER
			MAX-ACCESS	read-only
			STATUS	current
			::= { hmWanMbus2C 16 }

hmWanMbus2CValue05		OBJECT-TYPE
			SYNTAX	INTEGER
			MAX-ACCESS	read-only
			STATUS	current
			::= { hmWanMbus2C 17 }

hmWanMbus2CVIF06		OBJECT-TYPE
			SYNTAX	INTEGER
			MAX-ACCESS	read-only
			STATUS	current
			::= { hmWanMbus2C 18 }

hmWanMbus2CValue06		OBJECT-TYPE
			SYNTAX	INTEGER
			MAX-ACCESS	read-only
			STATUS	current
			::= { hmWanMbus2C 19 }

hmWanMbus2CVIF07		OBJECT-TYPE
			SYNTAX	INTEGER
			MAX-ACCESS	read-only
			STATUS	current
			::= { hmWanMbus2C 20 }

hmWanMbus2CValue07		OBJECT-TYPE
			SYNTAX	INTEGER
			MAX-ACCESS	read-only
			STATUS	current
			::= { hmWanMbus2C 21 }

hmWanMbus2CVIF08		OBJECT-TYPE
			SYNTAX	INTEGER
			MAX-ACCESS	read-only
			STATUS	current
			::= { hmWanMbus2C 22 }

hmWanMbus2CValue08		OBJECT-TYPE
			SYNTAX	INTEGER
			MAX-ACCESS	read-only
			STATUS	current
			::= { hmWanMbus2C 23 }

hmWanMbus2CVIF09		OBJECT-TYPE
			SYNTAX	INTEGER
			MAX-ACCESS	read-only
			STATUS	current
			::= { hmWanMbus2C 24 }

hmWanMbus2CValue09		OBJECT-TYPE
			SYNTAX	INTEGER
			MAX-ACCESS	read-only
			STATUS	current
			::= { hmWanMbus2C 25 }

hmWanMbus2CVIF0A		OBJECT-TYPE
			SYNTAX	INTEGER
			MAX-ACCESS	read-only
			STATUS	current
			::= { hmWanMbus2C 26 }

hmWanMbus2CValue0A		OBJECT-TYPE
			SYNTAX	INTEGER
			MAX-ACCESS	read-only
			STATUS	current
			::= { hmWanMbus2C 27 }

hmWanMbus2CVIF0B		OBJECT-TYPE
			SYNTAX	INTEGER
			MAX-ACCESS	read-only
			STATUS	current
			::= { hmWanMbus2C 28 }

hmWanMbus2CValue0B		OBJECT-TYPE
			SYNTAX	INTEGER
			MAX-ACCESS	read-only
			STATUS	current
			::= { hmWanMbus2C 29 }

hmWanMbus2CVIF0C		OBJECT-TYPE
			SYNTAX	INTEGER
			MAX-ACCESS	read-only
			STATUS	current
			::= { hmWanMbus2C 30 }

hmWanMbus2CValue0C		OBJECT-TYPE
			SYNTAX	INTEGER
			MAX-ACCESS	read-only
			STATUS	current
			::= { hmWanMbus2C 31 }

hmWanMbus2CVIF0D		OBJECT-TYPE
			SYNTAX	INTEGER
			MAX-ACCESS	read-only
			STATUS	current
			::= { hmWanMbus2C 32 }

hmWanMbus2CValue0D		OBJECT-TYPE
			SYNTAX	INTEGER
			MAX-ACCESS	read-only
			STATUS	current
			::= { hmWanMbus2C 33 }

hmWanMbus2CVIF0E		OBJECT-TYPE
			SYNTAX	INTEGER
			MAX-ACCESS	read-only
			STATUS	current
			::= { hmWanMbus2C 34 }

hmWanMbus2CValue0E		OBJECT-TYPE
			SYNTAX	INTEGER
			MAX-ACCESS	read-only
			STATUS	current
			::= { hmWanMbus2C 35 }

hmWanMbus2CVIF0F		OBJECT-TYPE
			SYNTAX	INTEGER
			MAX-ACCESS	read-only
			STATUS	current
			::= { hmWanMbus2C 36 }

hmWanMbus2CValue0F		OBJECT-TYPE
			SYNTAX	INTEGER
			MAX-ACCESS	read-only
			STATUS	current
			::= { hmWanMbus2C 37 }

hmWanMbus2CVIF10		OBJECT-TYPE
			SYNTAX	INTEGER
			MAX-ACCESS	read-only
			STATUS	current
			::= { hmWanMbus2C 38 }

hmWanMbus2CValue10		OBJECT-TYPE
			SYNTAX	INTEGER
			MAX-ACCESS	read-only
			STATUS	current
			::= { hmWanMbus2C 39 }

hmWanMbus2CVIF11		OBJECT-TYPE
			SYNTAX	INTEGER
			MAX-ACCESS	read-only
			STATUS	current
			::= { hmWanMbus2C 40 }

hmWanMbus2CValue11		OBJECT-TYPE
			SYNTAX	INTEGER
			MAX-ACCESS	read-only
			STATUS	current
			::= { hmWanMbus2C 41 }

hmWanMbus2CVIF12		OBJECT-TYPE
			SYNTAX	INTEGER
			MAX-ACCESS	read-only
			STATUS	current
			::= { hmWanMbus2C 42 }

hmWanMbus2CValue12		OBJECT-TYPE
			SYNTAX	INTEGER
			MAX-ACCESS	read-only
			STATUS	current
			::= { hmWanMbus2C 43 }

hmWanMbus2CVIF13		OBJECT-TYPE
			SYNTAX	INTEGER
			MAX-ACCESS	read-only
			STATUS	current
			::= { hmWanMbus2C 44 }

hmWanMbus2CValue13		OBJECT-TYPE
			SYNTAX	INTEGER
			MAX-ACCESS	read-only
			STATUS	current
			::= { hmWanMbus2C 45 }

hmWanMbus2CVIF14		OBJECT-TYPE
			SYNTAX	INTEGER
			MAX-ACCESS	read-only
			STATUS	current
			::= { hmWanMbus2C 46 }

hmWanMbus2CValue14		OBJECT-TYPE
			SYNTAX	INTEGER
			MAX-ACCESS	read-only
			STATUS	current
			::= { hmWanMbus2C 47 }

hmWanMbus2CVIF15		OBJECT-TYPE
			SYNTAX	INTEGER
			MAX-ACCESS	read-only
			STATUS	current
			::= { hmWanMbus2C 48 }

hmWanMbus2CValue15		OBJECT-TYPE
			SYNTAX	INTEGER
			MAX-ACCESS	read-only
			STATUS	current
			::= { hmWanMbus2C 49 }

hmWanMbus2CVIF16		OBJECT-TYPE
			SYNTAX	INTEGER
			MAX-ACCESS	read-only
			STATUS	current
			::= { hmWanMbus2C 50 }

hmWanMbus2CValue16		OBJECT-TYPE
			SYNTAX	INTEGER
			MAX-ACCESS	read-only
			STATUS	current
			::= { hmWanMbus2C 51 }

hmWanMbus2CVIF17		OBJECT-TYPE
			SYNTAX	INTEGER
			MAX-ACCESS	read-only
			STATUS	current
			::= { hmWanMbus2C 52 }

hmWanMbus2CValue17		OBJECT-TYPE
			SYNTAX	INTEGER
			MAX-ACCESS	read-only
			STATUS	current
			::= { hmWanMbus2C 53 }

hmWanMbus2CVIF18		OBJECT-TYPE
			SYNTAX	INTEGER
			MAX-ACCESS	read-only
			STATUS	current
			::= { hmWanMbus2C 54 }

hmWanMbus2CValue18		OBJECT-TYPE
			SYNTAX	INTEGER
			MAX-ACCESS	read-only
			STATUS	current
			::= { hmWanMbus2C 55 }

hmWanMbus2CVIF19		OBJECT-TYPE
			SYNTAX	INTEGER
			MAX-ACCESS	read-only
			STATUS	current
			::= { hmWanMbus2C 56 }

hmWanMbus2CValue19		OBJECT-TYPE
			SYNTAX	INTEGER
			MAX-ACCESS	read-only
			STATUS	current
			::= { hmWanMbus2C 57 }

hmWanMbus2CVIF1A		OBJECT-TYPE
			SYNTAX	INTEGER
			MAX-ACCESS	read-only
			STATUS	current
			::= { hmWanMbus2C 58 }

hmWanMbus2CValue1A		OBJECT-TYPE
			SYNTAX	INTEGER
			MAX-ACCESS	read-only
			STATUS	current
			::= { hmWanMbus2C 59 }

hmWanMbus2CVIF1B		OBJECT-TYPE
			SYNTAX	INTEGER
			MAX-ACCESS	read-only
			STATUS	current
			::= { hmWanMbus2C 60 }

hmWanMbus2CValue1B		OBJECT-TYPE
			SYNTAX	INTEGER
			MAX-ACCESS	read-only
			STATUS	current
			::= { hmWanMbus2C 61 }

hmWanMbus2CVIF1C		OBJECT-TYPE
			SYNTAX	INTEGER
			MAX-ACCESS	read-only
			STATUS	current
			::= { hmWanMbus2C 62 }

hmWanMbus2CValue1C		OBJECT-TYPE
			SYNTAX	INTEGER
			MAX-ACCESS	read-only
			STATUS	current
			::= { hmWanMbus2C 63 }

hmWanMbus2CVIF1D		OBJECT-TYPE
			SYNTAX	INTEGER
			MAX-ACCESS	read-only
			STATUS	current
			::= { hmWanMbus2C 64 }

hmWanMbus2CValue1D		OBJECT-TYPE
			SYNTAX	INTEGER
			MAX-ACCESS	read-only
			STATUS	current
			::= { hmWanMbus2C 65 }

hmWanMbus2CVIF1E		OBJECT-TYPE
			SYNTAX	INTEGER
			MAX-ACCESS	read-only
			STATUS	current
			::= { hmWanMbus2C 66 }

hmWanMbus2CValue1E		OBJECT-TYPE
			SYNTAX	INTEGER
			MAX-ACCESS	read-only
			STATUS	current
			::= { hmWanMbus2C 67 }

hmWanMbus2CVIF1F		OBJECT-TYPE
			SYNTAX	INTEGER
			MAX-ACCESS	read-only
			STATUS	current
			::= { hmWanMbus2C 68 }

hmWanMbus2CValue1F		OBJECT-TYPE
			SYNTAX	INTEGER
			MAX-ACCESS	read-only
			STATUS	current
			::= { hmWanMbus2C 69 }

hmWanMbus2CVIF20		OBJECT-TYPE
			SYNTAX	INTEGER
			MAX-ACCESS	read-only
			STATUS	current
			::= { hmWanMbus2C 70 }

hmWanMbus2CValue20		OBJECT-TYPE
			SYNTAX	INTEGER
			MAX-ACCESS	read-only
			STATUS	current
			::= { hmWanMbus2C 71 }

hmWanMbus2CVIF21		OBJECT-TYPE
			SYNTAX	INTEGER
			MAX-ACCESS	read-only
			STATUS	current
			::= { hmWanMbus2C 72 }

hmWanMbus2CValue21		OBJECT-TYPE
			SYNTAX	INTEGER
			MAX-ACCESS	read-only
			STATUS	current
			::= { hmWanMbus2C 73 }

hmWanMbus2CVIF22		OBJECT-TYPE
			SYNTAX	INTEGER
			MAX-ACCESS	read-only
			STATUS	current
			::= { hmWanMbus2C 74 }

hmWanMbus2CValue22		OBJECT-TYPE
			SYNTAX	INTEGER
			MAX-ACCESS	read-only
			STATUS	current
			::= { hmWanMbus2C 75 }

hmWanMbus2CVIF23		OBJECT-TYPE
			SYNTAX	INTEGER
			MAX-ACCESS	read-only
			STATUS	current
			::= { hmWanMbus2C 76 }

hmWanMbus2CValue23		OBJECT-TYPE
			SYNTAX	INTEGER
			MAX-ACCESS	read-only
			STATUS	current
			::= { hmWanMbus2C 77 }

hmWanMbus2CVIF24		OBJECT-TYPE
			SYNTAX	INTEGER
			MAX-ACCESS	read-only
			STATUS	current
			::= { hmWanMbus2C 78 }

hmWanMbus2CValue24		OBJECT-TYPE
			SYNTAX	INTEGER
			MAX-ACCESS	read-only
			STATUS	current
			::= { hmWanMbus2C 79 }

hmWanMbus2CVIF25		OBJECT-TYPE
			SYNTAX	INTEGER
			MAX-ACCESS	read-only
			STATUS	current
			::= { hmWanMbus2C 80 }

hmWanMbus2CValue25		OBJECT-TYPE
			SYNTAX	INTEGER
			MAX-ACCESS	read-only
			STATUS	current
			::= { hmWanMbus2C 81 }

hmWanMbus2CVIF26		OBJECT-TYPE
			SYNTAX	INTEGER
			MAX-ACCESS	read-only
			STATUS	current
			::= { hmWanMbus2C 82 }

hmWanMbus2CValue26		OBJECT-TYPE
			SYNTAX	INTEGER
			MAX-ACCESS	read-only
			STATUS	current
			::= { hmWanMbus2C 83 }

hmWanMbus2CVIF27		OBJECT-TYPE
			SYNTAX	INTEGER
			MAX-ACCESS	read-only
			STATUS	current
			::= { hmWanMbus2C 84 }

hmWanMbus2CValue27		OBJECT-TYPE
			SYNTAX	INTEGER
			MAX-ACCESS	read-only
			STATUS	current
			::= { hmWanMbus2C 85 }

hmWanMbus2CVIF28		OBJECT-TYPE
			SYNTAX	INTEGER
			MAX-ACCESS	read-only
			STATUS	current
			::= { hmWanMbus2C 86 }

hmWanMbus2CValue28		OBJECT-TYPE
			SYNTAX	INTEGER
			MAX-ACCESS	read-only
			STATUS	current
			::= { hmWanMbus2C 87 }

hmWanMbus2CVIF29		OBJECT-TYPE
			SYNTAX	INTEGER
			MAX-ACCESS	read-only
			STATUS	current
			::= { hmWanMbus2C 88 }

hmWanMbus2CValue29		OBJECT-TYPE
			SYNTAX	INTEGER
			MAX-ACCESS	read-only
			STATUS	current
			::= { hmWanMbus2C 89 }

hmWanMbus2CVIF2A		OBJECT-TYPE
			SYNTAX	INTEGER
			MAX-ACCESS	read-only
			STATUS	current
			::= { hmWanMbus2C 90 }

hmWanMbus2CValue2A		OBJECT-TYPE
			SYNTAX	INTEGER
			MAX-ACCESS	read-only
			STATUS	current
			::= { hmWanMbus2C 91 }

hmWanMbus2CVIF2B		OBJECT-TYPE
			SYNTAX	INTEGER
			MAX-ACCESS	read-only
			STATUS	current
			::= { hmWanMbus2C 92 }

hmWanMbus2CValue2B		OBJECT-TYPE
			SYNTAX	INTEGER
			MAX-ACCESS	read-only
			STATUS	current
			::= { hmWanMbus2C 93 }

hmWanMbus2CVIF2C		OBJECT-TYPE
			SYNTAX	INTEGER
			MAX-ACCESS	read-only
			STATUS	current
			::= { hmWanMbus2C 94 }

hmWanMbus2CValue2C		OBJECT-TYPE
			SYNTAX	INTEGER
			MAX-ACCESS	read-only
			STATUS	current
			::= { hmWanMbus2C 95 }

hmWanMbus2CVIF2D		OBJECT-TYPE
			SYNTAX	INTEGER
			MAX-ACCESS	read-only
			STATUS	current
			::= { hmWanMbus2C 96 }

hmWanMbus2CValue2D		OBJECT-TYPE
			SYNTAX	INTEGER
			MAX-ACCESS	read-only
			STATUS	current
			::= { hmWanMbus2C 97 }

hmWanMbus2CVIF2E		OBJECT-TYPE
			SYNTAX	INTEGER
			MAX-ACCESS	read-only
			STATUS	current
			::= { hmWanMbus2C 98 }

hmWanMbus2CValue2E		OBJECT-TYPE
			SYNTAX	INTEGER
			MAX-ACCESS	read-only
			STATUS	current
			::= { hmWanMbus2C 99 }

hmWanMbus2CVIF2F		OBJECT-TYPE
			SYNTAX	INTEGER
			MAX-ACCESS	read-only
			STATUS	current
			::= { hmWanMbus2C 100 }

hmWanMbus2CValue2F		OBJECT-TYPE
			SYNTAX	INTEGER
			MAX-ACCESS	read-only
			STATUS	current
			::= { hmWanMbus2C 101 }

hmWanMbus2D			OBJECT IDENTIFIER ::= { hmWanMbus 45 }

hmWanMbus2DIdNumber		OBJECT-TYPE
			SYNTAX	Gauge32
			MAX-ACCESS	read-only
			STATUS	current
			::= { hmWanMbus2D 1 }

hmWanMbus2DManufacturer	OBJECT-TYPE
			SYNTAX	Gauge32
			MAX-ACCESS	read-only
			STATUS	current
			::= { hmWanMbus2D 2 }

hmWanMbus2DVersion		OBJECT-TYPE
			SYNTAX	Gauge32
			MAX-ACCESS	read-only
			STATUS	current
			::= { hmWanMbus2D 3 }

hmWanMbus2DMedium		OBJECT-TYPE
			SYNTAX	Gauge32
			MAX-ACCESS	read-only
			STATUS	current
			::= { hmWanMbus2D 4 }

hmWanMbus2DStatus		OBJECT-TYPE
			SYNTAX	Gauge32
			MAX-ACCESS	read-only
			STATUS	current
			::= { hmWanMbus2D 5 }

hmWanMbus2DVIF00		OBJECT-TYPE
			SYNTAX	INTEGER
			MAX-ACCESS	read-only
			STATUS	current
			::= { hmWanMbus2D 6 }

hmWanMbus2DValue00		OBJECT-TYPE
			SYNTAX	INTEGER
			MAX-ACCESS	read-only
			STATUS	current
			::= { hmWanMbus2D 7 }

hmWanMbus2DVIF01		OBJECT-TYPE
			SYNTAX	INTEGER
			MAX-ACCESS	read-only
			STATUS	current
			::= { hmWanMbus2D 8 }

hmWanMbus2DValue01		OBJECT-TYPE
			SYNTAX	INTEGER
			MAX-ACCESS	read-only
			STATUS	current
			::= { hmWanMbus2D 9 }

hmWanMbus2DVIF02		OBJECT-TYPE
			SYNTAX	INTEGER
			MAX-ACCESS	read-only
			STATUS	current
			::= { hmWanMbus2D 10 }

hmWanMbus2DValue02		OBJECT-TYPE
			SYNTAX	INTEGER
			MAX-ACCESS	read-only
			STATUS	current
			::= { hmWanMbus2D 11 }

hmWanMbus2DVIF03		OBJECT-TYPE
			SYNTAX	INTEGER
			MAX-ACCESS	read-only
			STATUS	current
			::= { hmWanMbus2D 12 }

hmWanMbus2DValue03		OBJECT-TYPE
			SYNTAX	INTEGER
			MAX-ACCESS	read-only
			STATUS	current
			::= { hmWanMbus2D 13 }

hmWanMbus2DVIF04		OBJECT-TYPE
			SYNTAX	INTEGER
			MAX-ACCESS	read-only
			STATUS	current
			::= { hmWanMbus2D 14 }

hmWanMbus2DValue04		OBJECT-TYPE
			SYNTAX	INTEGER
			MAX-ACCESS	read-only
			STATUS	current
			::= { hmWanMbus2D 15 }

hmWanMbus2DVIF05		OBJECT-TYPE
			SYNTAX	INTEGER
			MAX-ACCESS	read-only
			STATUS	current
			::= { hmWanMbus2D 16 }

hmWanMbus2DValue05		OBJECT-TYPE
			SYNTAX	INTEGER
			MAX-ACCESS	read-only
			STATUS	current
			::= { hmWanMbus2D 17 }

hmWanMbus2DVIF06		OBJECT-TYPE
			SYNTAX	INTEGER
			MAX-ACCESS	read-only
			STATUS	current
			::= { hmWanMbus2D 18 }

hmWanMbus2DValue06		OBJECT-TYPE
			SYNTAX	INTEGER
			MAX-ACCESS	read-only
			STATUS	current
			::= { hmWanMbus2D 19 }

hmWanMbus2DVIF07		OBJECT-TYPE
			SYNTAX	INTEGER
			MAX-ACCESS	read-only
			STATUS	current
			::= { hmWanMbus2D 20 }

hmWanMbus2DValue07		OBJECT-TYPE
			SYNTAX	INTEGER
			MAX-ACCESS	read-only
			STATUS	current
			::= { hmWanMbus2D 21 }

hmWanMbus2DVIF08		OBJECT-TYPE
			SYNTAX	INTEGER
			MAX-ACCESS	read-only
			STATUS	current
			::= { hmWanMbus2D 22 }

hmWanMbus2DValue08		OBJECT-TYPE
			SYNTAX	INTEGER
			MAX-ACCESS	read-only
			STATUS	current
			::= { hmWanMbus2D 23 }

hmWanMbus2DVIF09		OBJECT-TYPE
			SYNTAX	INTEGER
			MAX-ACCESS	read-only
			STATUS	current
			::= { hmWanMbus2D 24 }

hmWanMbus2DValue09		OBJECT-TYPE
			SYNTAX	INTEGER
			MAX-ACCESS	read-only
			STATUS	current
			::= { hmWanMbus2D 25 }

hmWanMbus2DVIF0A		OBJECT-TYPE
			SYNTAX	INTEGER
			MAX-ACCESS	read-only
			STATUS	current
			::= { hmWanMbus2D 26 }

hmWanMbus2DValue0A		OBJECT-TYPE
			SYNTAX	INTEGER
			MAX-ACCESS	read-only
			STATUS	current
			::= { hmWanMbus2D 27 }

hmWanMbus2DVIF0B		OBJECT-TYPE
			SYNTAX	INTEGER
			MAX-ACCESS	read-only
			STATUS	current
			::= { hmWanMbus2D 28 }

hmWanMbus2DValue0B		OBJECT-TYPE
			SYNTAX	INTEGER
			MAX-ACCESS	read-only
			STATUS	current
			::= { hmWanMbus2D 29 }

hmWanMbus2DVIF0C		OBJECT-TYPE
			SYNTAX	INTEGER
			MAX-ACCESS	read-only
			STATUS	current
			::= { hmWanMbus2D 30 }

hmWanMbus2DValue0C		OBJECT-TYPE
			SYNTAX	INTEGER
			MAX-ACCESS	read-only
			STATUS	current
			::= { hmWanMbus2D 31 }

hmWanMbus2DVIF0D		OBJECT-TYPE
			SYNTAX	INTEGER
			MAX-ACCESS	read-only
			STATUS	current
			::= { hmWanMbus2D 32 }

hmWanMbus2DValue0D		OBJECT-TYPE
			SYNTAX	INTEGER
			MAX-ACCESS	read-only
			STATUS	current
			::= { hmWanMbus2D 33 }

hmWanMbus2DVIF0E		OBJECT-TYPE
			SYNTAX	INTEGER
			MAX-ACCESS	read-only
			STATUS	current
			::= { hmWanMbus2D 34 }

hmWanMbus2DValue0E		OBJECT-TYPE
			SYNTAX	INTEGER
			MAX-ACCESS	read-only
			STATUS	current
			::= { hmWanMbus2D 35 }

hmWanMbus2DVIF0F		OBJECT-TYPE
			SYNTAX	INTEGER
			MAX-ACCESS	read-only
			STATUS	current
			::= { hmWanMbus2D 36 }

hmWanMbus2DValue0F		OBJECT-TYPE
			SYNTAX	INTEGER
			MAX-ACCESS	read-only
			STATUS	current
			::= { hmWanMbus2D 37 }

hmWanMbus2DVIF10		OBJECT-TYPE
			SYNTAX	INTEGER
			MAX-ACCESS	read-only
			STATUS	current
			::= { hmWanMbus2D 38 }

hmWanMbus2DValue10		OBJECT-TYPE
			SYNTAX	INTEGER
			MAX-ACCESS	read-only
			STATUS	current
			::= { hmWanMbus2D 39 }

hmWanMbus2DVIF11		OBJECT-TYPE
			SYNTAX	INTEGER
			MAX-ACCESS	read-only
			STATUS	current
			::= { hmWanMbus2D 40 }

hmWanMbus2DValue11		OBJECT-TYPE
			SYNTAX	INTEGER
			MAX-ACCESS	read-only
			STATUS	current
			::= { hmWanMbus2D 41 }

hmWanMbus2DVIF12		OBJECT-TYPE
			SYNTAX	INTEGER
			MAX-ACCESS	read-only
			STATUS	current
			::= { hmWanMbus2D 42 }

hmWanMbus2DValue12		OBJECT-TYPE
			SYNTAX	INTEGER
			MAX-ACCESS	read-only
			STATUS	current
			::= { hmWanMbus2D 43 }

hmWanMbus2DVIF13		OBJECT-TYPE
			SYNTAX	INTEGER
			MAX-ACCESS	read-only
			STATUS	current
			::= { hmWanMbus2D 44 }

hmWanMbus2DValue13		OBJECT-TYPE
			SYNTAX	INTEGER
			MAX-ACCESS	read-only
			STATUS	current
			::= { hmWanMbus2D 45 }

hmWanMbus2DVIF14		OBJECT-TYPE
			SYNTAX	INTEGER
			MAX-ACCESS	read-only
			STATUS	current
			::= { hmWanMbus2D 46 }

hmWanMbus2DValue14		OBJECT-TYPE
			SYNTAX	INTEGER
			MAX-ACCESS	read-only
			STATUS	current
			::= { hmWanMbus2D 47 }

hmWanMbus2DVIF15		OBJECT-TYPE
			SYNTAX	INTEGER
			MAX-ACCESS	read-only
			STATUS	current
			::= { hmWanMbus2D 48 }

hmWanMbus2DValue15		OBJECT-TYPE
			SYNTAX	INTEGER
			MAX-ACCESS	read-only
			STATUS	current
			::= { hmWanMbus2D 49 }

hmWanMbus2DVIF16		OBJECT-TYPE
			SYNTAX	INTEGER
			MAX-ACCESS	read-only
			STATUS	current
			::= { hmWanMbus2D 50 }

hmWanMbus2DValue16		OBJECT-TYPE
			SYNTAX	INTEGER
			MAX-ACCESS	read-only
			STATUS	current
			::= { hmWanMbus2D 51 }

hmWanMbus2DVIF17		OBJECT-TYPE
			SYNTAX	INTEGER
			MAX-ACCESS	read-only
			STATUS	current
			::= { hmWanMbus2D 52 }

hmWanMbus2DValue17		OBJECT-TYPE
			SYNTAX	INTEGER
			MAX-ACCESS	read-only
			STATUS	current
			::= { hmWanMbus2D 53 }

hmWanMbus2DVIF18		OBJECT-TYPE
			SYNTAX	INTEGER
			MAX-ACCESS	read-only
			STATUS	current
			::= { hmWanMbus2D 54 }

hmWanMbus2DValue18		OBJECT-TYPE
			SYNTAX	INTEGER
			MAX-ACCESS	read-only
			STATUS	current
			::= { hmWanMbus2D 55 }

hmWanMbus2DVIF19		OBJECT-TYPE
			SYNTAX	INTEGER
			MAX-ACCESS	read-only
			STATUS	current
			::= { hmWanMbus2D 56 }

hmWanMbus2DValue19		OBJECT-TYPE
			SYNTAX	INTEGER
			MAX-ACCESS	read-only
			STATUS	current
			::= { hmWanMbus2D 57 }

hmWanMbus2DVIF1A		OBJECT-TYPE
			SYNTAX	INTEGER
			MAX-ACCESS	read-only
			STATUS	current
			::= { hmWanMbus2D 58 }

hmWanMbus2DValue1A		OBJECT-TYPE
			SYNTAX	INTEGER
			MAX-ACCESS	read-only
			STATUS	current
			::= { hmWanMbus2D 59 }

hmWanMbus2DVIF1B		OBJECT-TYPE
			SYNTAX	INTEGER
			MAX-ACCESS	read-only
			STATUS	current
			::= { hmWanMbus2D 60 }

hmWanMbus2DValue1B		OBJECT-TYPE
			SYNTAX	INTEGER
			MAX-ACCESS	read-only
			STATUS	current
			::= { hmWanMbus2D 61 }

hmWanMbus2DVIF1C		OBJECT-TYPE
			SYNTAX	INTEGER
			MAX-ACCESS	read-only
			STATUS	current
			::= { hmWanMbus2D 62 }

hmWanMbus2DValue1C		OBJECT-TYPE
			SYNTAX	INTEGER
			MAX-ACCESS	read-only
			STATUS	current
			::= { hmWanMbus2D 63 }

hmWanMbus2DVIF1D		OBJECT-TYPE
			SYNTAX	INTEGER
			MAX-ACCESS	read-only
			STATUS	current
			::= { hmWanMbus2D 64 }

hmWanMbus2DValue1D		OBJECT-TYPE
			SYNTAX	INTEGER
			MAX-ACCESS	read-only
			STATUS	current
			::= { hmWanMbus2D 65 }

hmWanMbus2DVIF1E		OBJECT-TYPE
			SYNTAX	INTEGER
			MAX-ACCESS	read-only
			STATUS	current
			::= { hmWanMbus2D 66 }

hmWanMbus2DValue1E		OBJECT-TYPE
			SYNTAX	INTEGER
			MAX-ACCESS	read-only
			STATUS	current
			::= { hmWanMbus2D 67 }

hmWanMbus2DVIF1F		OBJECT-TYPE
			SYNTAX	INTEGER
			MAX-ACCESS	read-only
			STATUS	current
			::= { hmWanMbus2D 68 }

hmWanMbus2DValue1F		OBJECT-TYPE
			SYNTAX	INTEGER
			MAX-ACCESS	read-only
			STATUS	current
			::= { hmWanMbus2D 69 }

hmWanMbus2DVIF20		OBJECT-TYPE
			SYNTAX	INTEGER
			MAX-ACCESS	read-only
			STATUS	current
			::= { hmWanMbus2D 70 }

hmWanMbus2DValue20		OBJECT-TYPE
			SYNTAX	INTEGER
			MAX-ACCESS	read-only
			STATUS	current
			::= { hmWanMbus2D 71 }

hmWanMbus2DVIF21		OBJECT-TYPE
			SYNTAX	INTEGER
			MAX-ACCESS	read-only
			STATUS	current
			::= { hmWanMbus2D 72 }

hmWanMbus2DValue21		OBJECT-TYPE
			SYNTAX	INTEGER
			MAX-ACCESS	read-only
			STATUS	current
			::= { hmWanMbus2D 73 }

hmWanMbus2DVIF22		OBJECT-TYPE
			SYNTAX	INTEGER
			MAX-ACCESS	read-only
			STATUS	current
			::= { hmWanMbus2D 74 }

hmWanMbus2DValue22		OBJECT-TYPE
			SYNTAX	INTEGER
			MAX-ACCESS	read-only
			STATUS	current
			::= { hmWanMbus2D 75 }

hmWanMbus2DVIF23		OBJECT-TYPE
			SYNTAX	INTEGER
			MAX-ACCESS	read-only
			STATUS	current
			::= { hmWanMbus2D 76 }

hmWanMbus2DValue23		OBJECT-TYPE
			SYNTAX	INTEGER
			MAX-ACCESS	read-only
			STATUS	current
			::= { hmWanMbus2D 77 }

hmWanMbus2DVIF24		OBJECT-TYPE
			SYNTAX	INTEGER
			MAX-ACCESS	read-only
			STATUS	current
			::= { hmWanMbus2D 78 }

hmWanMbus2DValue24		OBJECT-TYPE
			SYNTAX	INTEGER
			MAX-ACCESS	read-only
			STATUS	current
			::= { hmWanMbus2D 79 }

hmWanMbus2DVIF25		OBJECT-TYPE
			SYNTAX	INTEGER
			MAX-ACCESS	read-only
			STATUS	current
			::= { hmWanMbus2D 80 }

hmWanMbus2DValue25		OBJECT-TYPE
			SYNTAX	INTEGER
			MAX-ACCESS	read-only
			STATUS	current
			::= { hmWanMbus2D 81 }

hmWanMbus2DVIF26		OBJECT-TYPE
			SYNTAX	INTEGER
			MAX-ACCESS	read-only
			STATUS	current
			::= { hmWanMbus2D 82 }

hmWanMbus2DValue26		OBJECT-TYPE
			SYNTAX	INTEGER
			MAX-ACCESS	read-only
			STATUS	current
			::= { hmWanMbus2D 83 }

hmWanMbus2DVIF27		OBJECT-TYPE
			SYNTAX	INTEGER
			MAX-ACCESS	read-only
			STATUS	current
			::= { hmWanMbus2D 84 }

hmWanMbus2DValue27		OBJECT-TYPE
			SYNTAX	INTEGER
			MAX-ACCESS	read-only
			STATUS	current
			::= { hmWanMbus2D 85 }

hmWanMbus2DVIF28		OBJECT-TYPE
			SYNTAX	INTEGER
			MAX-ACCESS	read-only
			STATUS	current
			::= { hmWanMbus2D 86 }

hmWanMbus2DValue28		OBJECT-TYPE
			SYNTAX	INTEGER
			MAX-ACCESS	read-only
			STATUS	current
			::= { hmWanMbus2D 87 }

hmWanMbus2DVIF29		OBJECT-TYPE
			SYNTAX	INTEGER
			MAX-ACCESS	read-only
			STATUS	current
			::= { hmWanMbus2D 88 }

hmWanMbus2DValue29		OBJECT-TYPE
			SYNTAX	INTEGER
			MAX-ACCESS	read-only
			STATUS	current
			::= { hmWanMbus2D 89 }

hmWanMbus2DVIF2A		OBJECT-TYPE
			SYNTAX	INTEGER
			MAX-ACCESS	read-only
			STATUS	current
			::= { hmWanMbus2D 90 }

hmWanMbus2DValue2A		OBJECT-TYPE
			SYNTAX	INTEGER
			MAX-ACCESS	read-only
			STATUS	current
			::= { hmWanMbus2D 91 }

hmWanMbus2DVIF2B		OBJECT-TYPE
			SYNTAX	INTEGER
			MAX-ACCESS	read-only
			STATUS	current
			::= { hmWanMbus2D 92 }

hmWanMbus2DValue2B		OBJECT-TYPE
			SYNTAX	INTEGER
			MAX-ACCESS	read-only
			STATUS	current
			::= { hmWanMbus2D 93 }

hmWanMbus2DVIF2C		OBJECT-TYPE
			SYNTAX	INTEGER
			MAX-ACCESS	read-only
			STATUS	current
			::= { hmWanMbus2D 94 }

hmWanMbus2DValue2C		OBJECT-TYPE
			SYNTAX	INTEGER
			MAX-ACCESS	read-only
			STATUS	current
			::= { hmWanMbus2D 95 }

hmWanMbus2DVIF2D		OBJECT-TYPE
			SYNTAX	INTEGER
			MAX-ACCESS	read-only
			STATUS	current
			::= { hmWanMbus2D 96 }

hmWanMbus2DValue2D		OBJECT-TYPE
			SYNTAX	INTEGER
			MAX-ACCESS	read-only
			STATUS	current
			::= { hmWanMbus2D 97 }

hmWanMbus2DVIF2E		OBJECT-TYPE
			SYNTAX	INTEGER
			MAX-ACCESS	read-only
			STATUS	current
			::= { hmWanMbus2D 98 }

hmWanMbus2DValue2E		OBJECT-TYPE
			SYNTAX	INTEGER
			MAX-ACCESS	read-only
			STATUS	current
			::= { hmWanMbus2D 99 }

hmWanMbus2DVIF2F		OBJECT-TYPE
			SYNTAX	INTEGER
			MAX-ACCESS	read-only
			STATUS	current
			::= { hmWanMbus2D 100 }

hmWanMbus2DValue2F		OBJECT-TYPE
			SYNTAX	INTEGER
			MAX-ACCESS	read-only
			STATUS	current
			::= { hmWanMbus2D 101 }

hmWanMbus2E			OBJECT IDENTIFIER ::= { hmWanMbus 46 }

hmWanMbus2EIdNumber		OBJECT-TYPE
			SYNTAX	Gauge32
			MAX-ACCESS	read-only
			STATUS	current
			::= { hmWanMbus2E 1 }

hmWanMbus2EManufacturer	OBJECT-TYPE
			SYNTAX	Gauge32
			MAX-ACCESS	read-only
			STATUS	current
			::= { hmWanMbus2E 2 }

hmWanMbus2EVersion		OBJECT-TYPE
			SYNTAX	Gauge32
			MAX-ACCESS	read-only
			STATUS	current
			::= { hmWanMbus2E 3 }

hmWanMbus2EMedium		OBJECT-TYPE
			SYNTAX	Gauge32
			MAX-ACCESS	read-only
			STATUS	current
			::= { hmWanMbus2E 4 }

hmWanMbus2EStatus		OBJECT-TYPE
			SYNTAX	Gauge32
			MAX-ACCESS	read-only
			STATUS	current
			::= { hmWanMbus2E 5 }

hmWanMbus2EVIF00		OBJECT-TYPE
			SYNTAX	INTEGER
			MAX-ACCESS	read-only
			STATUS	current
			::= { hmWanMbus2E 6 }

hmWanMbus2EValue00		OBJECT-TYPE
			SYNTAX	INTEGER
			MAX-ACCESS	read-only
			STATUS	current
			::= { hmWanMbus2E 7 }

hmWanMbus2EVIF01		OBJECT-TYPE
			SYNTAX	INTEGER
			MAX-ACCESS	read-only
			STATUS	current
			::= { hmWanMbus2E 8 }

hmWanMbus2EValue01		OBJECT-TYPE
			SYNTAX	INTEGER
			MAX-ACCESS	read-only
			STATUS	current
			::= { hmWanMbus2E 9 }

hmWanMbus2EVIF02		OBJECT-TYPE
			SYNTAX	INTEGER
			MAX-ACCESS	read-only
			STATUS	current
			::= { hmWanMbus2E 10 }

hmWanMbus2EValue02		OBJECT-TYPE
			SYNTAX	INTEGER
			MAX-ACCESS	read-only
			STATUS	current
			::= { hmWanMbus2E 11 }

hmWanMbus2EVIF03		OBJECT-TYPE
			SYNTAX	INTEGER
			MAX-ACCESS	read-only
			STATUS	current
			::= { hmWanMbus2E 12 }

hmWanMbus2EValue03		OBJECT-TYPE
			SYNTAX	INTEGER
			MAX-ACCESS	read-only
			STATUS	current
			::= { hmWanMbus2E 13 }

hmWanMbus2EVIF04		OBJECT-TYPE
			SYNTAX	INTEGER
			MAX-ACCESS	read-only
			STATUS	current
			::= { hmWanMbus2E 14 }

hmWanMbus2EValue04		OBJECT-TYPE
			SYNTAX	INTEGER
			MAX-ACCESS	read-only
			STATUS	current
			::= { hmWanMbus2E 15 }

hmWanMbus2EVIF05		OBJECT-TYPE
			SYNTAX	INTEGER
			MAX-ACCESS	read-only
			STATUS	current
			::= { hmWanMbus2E 16 }

hmWanMbus2EValue05		OBJECT-TYPE
			SYNTAX	INTEGER
			MAX-ACCESS	read-only
			STATUS	current
			::= { hmWanMbus2E 17 }

hmWanMbus2EVIF06		OBJECT-TYPE
			SYNTAX	INTEGER
			MAX-ACCESS	read-only
			STATUS	current
			::= { hmWanMbus2E 18 }

hmWanMbus2EValue06		OBJECT-TYPE
			SYNTAX	INTEGER
			MAX-ACCESS	read-only
			STATUS	current
			::= { hmWanMbus2E 19 }

hmWanMbus2EVIF07		OBJECT-TYPE
			SYNTAX	INTEGER
			MAX-ACCESS	read-only
			STATUS	current
			::= { hmWanMbus2E 20 }

hmWanMbus2EValue07		OBJECT-TYPE
			SYNTAX	INTEGER
			MAX-ACCESS	read-only
			STATUS	current
			::= { hmWanMbus2E 21 }

hmWanMbus2EVIF08		OBJECT-TYPE
			SYNTAX	INTEGER
			MAX-ACCESS	read-only
			STATUS	current
			::= { hmWanMbus2E 22 }

hmWanMbus2EValue08		OBJECT-TYPE
			SYNTAX	INTEGER
			MAX-ACCESS	read-only
			STATUS	current
			::= { hmWanMbus2E 23 }

hmWanMbus2EVIF09		OBJECT-TYPE
			SYNTAX	INTEGER
			MAX-ACCESS	read-only
			STATUS	current
			::= { hmWanMbus2E 24 }

hmWanMbus2EValue09		OBJECT-TYPE
			SYNTAX	INTEGER
			MAX-ACCESS	read-only
			STATUS	current
			::= { hmWanMbus2E 25 }

hmWanMbus2EVIF0A		OBJECT-TYPE
			SYNTAX	INTEGER
			MAX-ACCESS	read-only
			STATUS	current
			::= { hmWanMbus2E 26 }

hmWanMbus2EValue0A		OBJECT-TYPE
			SYNTAX	INTEGER
			MAX-ACCESS	read-only
			STATUS	current
			::= { hmWanMbus2E 27 }

hmWanMbus2EVIF0B		OBJECT-TYPE
			SYNTAX	INTEGER
			MAX-ACCESS	read-only
			STATUS	current
			::= { hmWanMbus2E 28 }

hmWanMbus2EValue0B		OBJECT-TYPE
			SYNTAX	INTEGER
			MAX-ACCESS	read-only
			STATUS	current
			::= { hmWanMbus2E 29 }

hmWanMbus2EVIF0C		OBJECT-TYPE
			SYNTAX	INTEGER
			MAX-ACCESS	read-only
			STATUS	current
			::= { hmWanMbus2E 30 }

hmWanMbus2EValue0C		OBJECT-TYPE
			SYNTAX	INTEGER
			MAX-ACCESS	read-only
			STATUS	current
			::= { hmWanMbus2E 31 }

hmWanMbus2EVIF0D		OBJECT-TYPE
			SYNTAX	INTEGER
			MAX-ACCESS	read-only
			STATUS	current
			::= { hmWanMbus2E 32 }

hmWanMbus2EValue0D		OBJECT-TYPE
			SYNTAX	INTEGER
			MAX-ACCESS	read-only
			STATUS	current
			::= { hmWanMbus2E 33 }

hmWanMbus2EVIF0E		OBJECT-TYPE
			SYNTAX	INTEGER
			MAX-ACCESS	read-only
			STATUS	current
			::= { hmWanMbus2E 34 }

hmWanMbus2EValue0E		OBJECT-TYPE
			SYNTAX	INTEGER
			MAX-ACCESS	read-only
			STATUS	current
			::= { hmWanMbus2E 35 }

hmWanMbus2EVIF0F		OBJECT-TYPE
			SYNTAX	INTEGER
			MAX-ACCESS	read-only
			STATUS	current
			::= { hmWanMbus2E 36 }

hmWanMbus2EValue0F		OBJECT-TYPE
			SYNTAX	INTEGER
			MAX-ACCESS	read-only
			STATUS	current
			::= { hmWanMbus2E 37 }

hmWanMbus2EVIF10		OBJECT-TYPE
			SYNTAX	INTEGER
			MAX-ACCESS	read-only
			STATUS	current
			::= { hmWanMbus2E 38 }

hmWanMbus2EValue10		OBJECT-TYPE
			SYNTAX	INTEGER
			MAX-ACCESS	read-only
			STATUS	current
			::= { hmWanMbus2E 39 }

hmWanMbus2EVIF11		OBJECT-TYPE
			SYNTAX	INTEGER
			MAX-ACCESS	read-only
			STATUS	current
			::= { hmWanMbus2E 40 }

hmWanMbus2EValue11		OBJECT-TYPE
			SYNTAX	INTEGER
			MAX-ACCESS	read-only
			STATUS	current
			::= { hmWanMbus2E 41 }

hmWanMbus2EVIF12		OBJECT-TYPE
			SYNTAX	INTEGER
			MAX-ACCESS	read-only
			STATUS	current
			::= { hmWanMbus2E 42 }

hmWanMbus2EValue12		OBJECT-TYPE
			SYNTAX	INTEGER
			MAX-ACCESS	read-only
			STATUS	current
			::= { hmWanMbus2E 43 }

hmWanMbus2EVIF13		OBJECT-TYPE
			SYNTAX	INTEGER
			MAX-ACCESS	read-only
			STATUS	current
			::= { hmWanMbus2E 44 }

hmWanMbus2EValue13		OBJECT-TYPE
			SYNTAX	INTEGER
			MAX-ACCESS	read-only
			STATUS	current
			::= { hmWanMbus2E 45 }

hmWanMbus2EVIF14		OBJECT-TYPE
			SYNTAX	INTEGER
			MAX-ACCESS	read-only
			STATUS	current
			::= { hmWanMbus2E 46 }

hmWanMbus2EValue14		OBJECT-TYPE
			SYNTAX	INTEGER
			MAX-ACCESS	read-only
			STATUS	current
			::= { hmWanMbus2E 47 }

hmWanMbus2EVIF15		OBJECT-TYPE
			SYNTAX	INTEGER
			MAX-ACCESS	read-only
			STATUS	current
			::= { hmWanMbus2E 48 }

hmWanMbus2EValue15		OBJECT-TYPE
			SYNTAX	INTEGER
			MAX-ACCESS	read-only
			STATUS	current
			::= { hmWanMbus2E 49 }

hmWanMbus2EVIF16		OBJECT-TYPE
			SYNTAX	INTEGER
			MAX-ACCESS	read-only
			STATUS	current
			::= { hmWanMbus2E 50 }

hmWanMbus2EValue16		OBJECT-TYPE
			SYNTAX	INTEGER
			MAX-ACCESS	read-only
			STATUS	current
			::= { hmWanMbus2E 51 }

hmWanMbus2EVIF17		OBJECT-TYPE
			SYNTAX	INTEGER
			MAX-ACCESS	read-only
			STATUS	current
			::= { hmWanMbus2E 52 }

hmWanMbus2EValue17		OBJECT-TYPE
			SYNTAX	INTEGER
			MAX-ACCESS	read-only
			STATUS	current
			::= { hmWanMbus2E 53 }

hmWanMbus2EVIF18		OBJECT-TYPE
			SYNTAX	INTEGER
			MAX-ACCESS	read-only
			STATUS	current
			::= { hmWanMbus2E 54 }

hmWanMbus2EValue18		OBJECT-TYPE
			SYNTAX	INTEGER
			MAX-ACCESS	read-only
			STATUS	current
			::= { hmWanMbus2E 55 }

hmWanMbus2EVIF19		OBJECT-TYPE
			SYNTAX	INTEGER
			MAX-ACCESS	read-only
			STATUS	current
			::= { hmWanMbus2E 56 }

hmWanMbus2EValue19		OBJECT-TYPE
			SYNTAX	INTEGER
			MAX-ACCESS	read-only
			STATUS	current
			::= { hmWanMbus2E 57 }

hmWanMbus2EVIF1A		OBJECT-TYPE
			SYNTAX	INTEGER
			MAX-ACCESS	read-only
			STATUS	current
			::= { hmWanMbus2E 58 }

hmWanMbus2EValue1A		OBJECT-TYPE
			SYNTAX	INTEGER
			MAX-ACCESS	read-only
			STATUS	current
			::= { hmWanMbus2E 59 }

hmWanMbus2EVIF1B		OBJECT-TYPE
			SYNTAX	INTEGER
			MAX-ACCESS	read-only
			STATUS	current
			::= { hmWanMbus2E 60 }

hmWanMbus2EValue1B		OBJECT-TYPE
			SYNTAX	INTEGER
			MAX-ACCESS	read-only
			STATUS	current
			::= { hmWanMbus2E 61 }

hmWanMbus2EVIF1C		OBJECT-TYPE
			SYNTAX	INTEGER
			MAX-ACCESS	read-only
			STATUS	current
			::= { hmWanMbus2E 62 }

hmWanMbus2EValue1C		OBJECT-TYPE
			SYNTAX	INTEGER
			MAX-ACCESS	read-only
			STATUS	current
			::= { hmWanMbus2E 63 }

hmWanMbus2EVIF1D		OBJECT-TYPE
			SYNTAX	INTEGER
			MAX-ACCESS	read-only
			STATUS	current
			::= { hmWanMbus2E 64 }

hmWanMbus2EValue1D		OBJECT-TYPE
			SYNTAX	INTEGER
			MAX-ACCESS	read-only
			STATUS	current
			::= { hmWanMbus2E 65 }

hmWanMbus2EVIF1E		OBJECT-TYPE
			SYNTAX	INTEGER
			MAX-ACCESS	read-only
			STATUS	current
			::= { hmWanMbus2E 66 }

hmWanMbus2EValue1E		OBJECT-TYPE
			SYNTAX	INTEGER
			MAX-ACCESS	read-only
			STATUS	current
			::= { hmWanMbus2E 67 }

hmWanMbus2EVIF1F		OBJECT-TYPE
			SYNTAX	INTEGER
			MAX-ACCESS	read-only
			STATUS	current
			::= { hmWanMbus2E 68 }

hmWanMbus2EValue1F		OBJECT-TYPE
			SYNTAX	INTEGER
			MAX-ACCESS	read-only
			STATUS	current
			::= { hmWanMbus2E 69 }

hmWanMbus2EVIF20		OBJECT-TYPE
			SYNTAX	INTEGER
			MAX-ACCESS	read-only
			STATUS	current
			::= { hmWanMbus2E 70 }

hmWanMbus2EValue20		OBJECT-TYPE
			SYNTAX	INTEGER
			MAX-ACCESS	read-only
			STATUS	current
			::= { hmWanMbus2E 71 }

hmWanMbus2EVIF21		OBJECT-TYPE
			SYNTAX	INTEGER
			MAX-ACCESS	read-only
			STATUS	current
			::= { hmWanMbus2E 72 }

hmWanMbus2EValue21		OBJECT-TYPE
			SYNTAX	INTEGER
			MAX-ACCESS	read-only
			STATUS	current
			::= { hmWanMbus2E 73 }

hmWanMbus2EVIF22		OBJECT-TYPE
			SYNTAX	INTEGER
			MAX-ACCESS	read-only
			STATUS	current
			::= { hmWanMbus2E 74 }

hmWanMbus2EValue22		OBJECT-TYPE
			SYNTAX	INTEGER
			MAX-ACCESS	read-only
			STATUS	current
			::= { hmWanMbus2E 75 }

hmWanMbus2EVIF23		OBJECT-TYPE
			SYNTAX	INTEGER
			MAX-ACCESS	read-only
			STATUS	current
			::= { hmWanMbus2E 76 }

hmWanMbus2EValue23		OBJECT-TYPE
			SYNTAX	INTEGER
			MAX-ACCESS	read-only
			STATUS	current
			::= { hmWanMbus2E 77 }

hmWanMbus2EVIF24		OBJECT-TYPE
			SYNTAX	INTEGER
			MAX-ACCESS	read-only
			STATUS	current
			::= { hmWanMbus2E 78 }

hmWanMbus2EValue24		OBJECT-TYPE
			SYNTAX	INTEGER
			MAX-ACCESS	read-only
			STATUS	current
			::= { hmWanMbus2E 79 }

hmWanMbus2EVIF25		OBJECT-TYPE
			SYNTAX	INTEGER
			MAX-ACCESS	read-only
			STATUS	current
			::= { hmWanMbus2E 80 }

hmWanMbus2EValue25		OBJECT-TYPE
			SYNTAX	INTEGER
			MAX-ACCESS	read-only
			STATUS	current
			::= { hmWanMbus2E 81 }

hmWanMbus2EVIF26		OBJECT-TYPE
			SYNTAX	INTEGER
			MAX-ACCESS	read-only
			STATUS	current
			::= { hmWanMbus2E 82 }

hmWanMbus2EValue26		OBJECT-TYPE
			SYNTAX	INTEGER
			MAX-ACCESS	read-only
			STATUS	current
			::= { hmWanMbus2E 83 }

hmWanMbus2EVIF27		OBJECT-TYPE
			SYNTAX	INTEGER
			MAX-ACCESS	read-only
			STATUS	current
			::= { hmWanMbus2E 84 }

hmWanMbus2EValue27		OBJECT-TYPE
			SYNTAX	INTEGER
			MAX-ACCESS	read-only
			STATUS	current
			::= { hmWanMbus2E 85 }

hmWanMbus2EVIF28		OBJECT-TYPE
			SYNTAX	INTEGER
			MAX-ACCESS	read-only
			STATUS	current
			::= { hmWanMbus2E 86 }

hmWanMbus2EValue28		OBJECT-TYPE
			SYNTAX	INTEGER
			MAX-ACCESS	read-only
			STATUS	current
			::= { hmWanMbus2E 87 }

hmWanMbus2EVIF29		OBJECT-TYPE
			SYNTAX	INTEGER
			MAX-ACCESS	read-only
			STATUS	current
			::= { hmWanMbus2E 88 }

hmWanMbus2EValue29		OBJECT-TYPE
			SYNTAX	INTEGER
			MAX-ACCESS	read-only
			STATUS	current
			::= { hmWanMbus2E 89 }

hmWanMbus2EVIF2A		OBJECT-TYPE
			SYNTAX	INTEGER
			MAX-ACCESS	read-only
			STATUS	current
			::= { hmWanMbus2E 90 }

hmWanMbus2EValue2A		OBJECT-TYPE
			SYNTAX	INTEGER
			MAX-ACCESS	read-only
			STATUS	current
			::= { hmWanMbus2E 91 }

hmWanMbus2EVIF2B		OBJECT-TYPE
			SYNTAX	INTEGER
			MAX-ACCESS	read-only
			STATUS	current
			::= { hmWanMbus2E 92 }

hmWanMbus2EValue2B		OBJECT-TYPE
			SYNTAX	INTEGER
			MAX-ACCESS	read-only
			STATUS	current
			::= { hmWanMbus2E 93 }

hmWanMbus2EVIF2C		OBJECT-TYPE
			SYNTAX	INTEGER
			MAX-ACCESS	read-only
			STATUS	current
			::= { hmWanMbus2E 94 }

hmWanMbus2EValue2C		OBJECT-TYPE
			SYNTAX	INTEGER
			MAX-ACCESS	read-only
			STATUS	current
			::= { hmWanMbus2E 95 }

hmWanMbus2EVIF2D		OBJECT-TYPE
			SYNTAX	INTEGER
			MAX-ACCESS	read-only
			STATUS	current
			::= { hmWanMbus2E 96 }

hmWanMbus2EValue2D		OBJECT-TYPE
			SYNTAX	INTEGER
			MAX-ACCESS	read-only
			STATUS	current
			::= { hmWanMbus2E 97 }

hmWanMbus2EVIF2E		OBJECT-TYPE
			SYNTAX	INTEGER
			MAX-ACCESS	read-only
			STATUS	current
			::= { hmWanMbus2E 98 }

hmWanMbus2EValue2E		OBJECT-TYPE
			SYNTAX	INTEGER
			MAX-ACCESS	read-only
			STATUS	current
			::= { hmWanMbus2E 99 }

hmWanMbus2EVIF2F		OBJECT-TYPE
			SYNTAX	INTEGER
			MAX-ACCESS	read-only
			STATUS	current
			::= { hmWanMbus2E 100 }

hmWanMbus2EValue2F		OBJECT-TYPE
			SYNTAX	INTEGER
			MAX-ACCESS	read-only
			STATUS	current
			::= { hmWanMbus2E 101 }

hmWanMbus2F			OBJECT IDENTIFIER ::= { hmWanMbus 47 }

hmWanMbus2FIdNumber		OBJECT-TYPE
			SYNTAX	Gauge32
			MAX-ACCESS	read-only
			STATUS	current
			::= { hmWanMbus2F 1 }

hmWanMbus2FManufacturer	OBJECT-TYPE
			SYNTAX	Gauge32
			MAX-ACCESS	read-only
			STATUS	current
			::= { hmWanMbus2F 2 }

hmWanMbus2FVersion		OBJECT-TYPE
			SYNTAX	Gauge32
			MAX-ACCESS	read-only
			STATUS	current
			::= { hmWanMbus2F 3 }

hmWanMbus2FMedium		OBJECT-TYPE
			SYNTAX	Gauge32
			MAX-ACCESS	read-only
			STATUS	current
			::= { hmWanMbus2F 4 }

hmWanMbus2FStatus		OBJECT-TYPE
			SYNTAX	Gauge32
			MAX-ACCESS	read-only
			STATUS	current
			::= { hmWanMbus2F 5 }

hmWanMbus2FVIF00		OBJECT-TYPE
			SYNTAX	INTEGER
			MAX-ACCESS	read-only
			STATUS	current
			::= { hmWanMbus2F 6 }

hmWanMbus2FValue00		OBJECT-TYPE
			SYNTAX	INTEGER
			MAX-ACCESS	read-only
			STATUS	current
			::= { hmWanMbus2F 7 }

hmWanMbus2FVIF01		OBJECT-TYPE
			SYNTAX	INTEGER
			MAX-ACCESS	read-only
			STATUS	current
			::= { hmWanMbus2F 8 }

hmWanMbus2FValue01		OBJECT-TYPE
			SYNTAX	INTEGER
			MAX-ACCESS	read-only
			STATUS	current
			::= { hmWanMbus2F 9 }

hmWanMbus2FVIF02		OBJECT-TYPE
			SYNTAX	INTEGER
			MAX-ACCESS	read-only
			STATUS	current
			::= { hmWanMbus2F 10 }

hmWanMbus2FValue02		OBJECT-TYPE
			SYNTAX	INTEGER
			MAX-ACCESS	read-only
			STATUS	current
			::= { hmWanMbus2F 11 }

hmWanMbus2FVIF03		OBJECT-TYPE
			SYNTAX	INTEGER
			MAX-ACCESS	read-only
			STATUS	current
			::= { hmWanMbus2F 12 }

hmWanMbus2FValue03		OBJECT-TYPE
			SYNTAX	INTEGER
			MAX-ACCESS	read-only
			STATUS	current
			::= { hmWanMbus2F 13 }

hmWanMbus2FVIF04		OBJECT-TYPE
			SYNTAX	INTEGER
			MAX-ACCESS	read-only
			STATUS	current
			::= { hmWanMbus2F 14 }

hmWanMbus2FValue04		OBJECT-TYPE
			SYNTAX	INTEGER
			MAX-ACCESS	read-only
			STATUS	current
			::= { hmWanMbus2F 15 }

hmWanMbus2FVIF05		OBJECT-TYPE
			SYNTAX	INTEGER
			MAX-ACCESS	read-only
			STATUS	current
			::= { hmWanMbus2F 16 }

hmWanMbus2FValue05		OBJECT-TYPE
			SYNTAX	INTEGER
			MAX-ACCESS	read-only
			STATUS	current
			::= { hmWanMbus2F 17 }

hmWanMbus2FVIF06		OBJECT-TYPE
			SYNTAX	INTEGER
			MAX-ACCESS	read-only
			STATUS	current
			::= { hmWanMbus2F 18 }

hmWanMbus2FValue06		OBJECT-TYPE
			SYNTAX	INTEGER
			MAX-ACCESS	read-only
			STATUS	current
			::= { hmWanMbus2F 19 }

hmWanMbus2FVIF07		OBJECT-TYPE
			SYNTAX	INTEGER
			MAX-ACCESS	read-only
			STATUS	current
			::= { hmWanMbus2F 20 }

hmWanMbus2FValue07		OBJECT-TYPE
			SYNTAX	INTEGER
			MAX-ACCESS	read-only
			STATUS	current
			::= { hmWanMbus2F 21 }

hmWanMbus2FVIF08		OBJECT-TYPE
			SYNTAX	INTEGER
			MAX-ACCESS	read-only
			STATUS	current
			::= { hmWanMbus2F 22 }

hmWanMbus2FValue08		OBJECT-TYPE
			SYNTAX	INTEGER
			MAX-ACCESS	read-only
			STATUS	current
			::= { hmWanMbus2F 23 }

hmWanMbus2FVIF09		OBJECT-TYPE
			SYNTAX	INTEGER
			MAX-ACCESS	read-only
			STATUS	current
			::= { hmWanMbus2F 24 }

hmWanMbus2FValue09		OBJECT-TYPE
			SYNTAX	INTEGER
			MAX-ACCESS	read-only
			STATUS	current
			::= { hmWanMbus2F 25 }

hmWanMbus2FVIF0A		OBJECT-TYPE
			SYNTAX	INTEGER
			MAX-ACCESS	read-only
			STATUS	current
			::= { hmWanMbus2F 26 }

hmWanMbus2FValue0A		OBJECT-TYPE
			SYNTAX	INTEGER
			MAX-ACCESS	read-only
			STATUS	current
			::= { hmWanMbus2F 27 }

hmWanMbus2FVIF0B		OBJECT-TYPE
			SYNTAX	INTEGER
			MAX-ACCESS	read-only
			STATUS	current
			::= { hmWanMbus2F 28 }

hmWanMbus2FValue0B		OBJECT-TYPE
			SYNTAX	INTEGER
			MAX-ACCESS	read-only
			STATUS	current
			::= { hmWanMbus2F 29 }

hmWanMbus2FVIF0C		OBJECT-TYPE
			SYNTAX	INTEGER
			MAX-ACCESS	read-only
			STATUS	current
			::= { hmWanMbus2F 30 }

hmWanMbus2FValue0C		OBJECT-TYPE
			SYNTAX	INTEGER
			MAX-ACCESS	read-only
			STATUS	current
			::= { hmWanMbus2F 31 }

hmWanMbus2FVIF0D		OBJECT-TYPE
			SYNTAX	INTEGER
			MAX-ACCESS	read-only
			STATUS	current
			::= { hmWanMbus2F 32 }

hmWanMbus2FValue0D		OBJECT-TYPE
			SYNTAX	INTEGER
			MAX-ACCESS	read-only
			STATUS	current
			::= { hmWanMbus2F 33 }

hmWanMbus2FVIF0E		OBJECT-TYPE
			SYNTAX	INTEGER
			MAX-ACCESS	read-only
			STATUS	current
			::= { hmWanMbus2F 34 }

hmWanMbus2FValue0E		OBJECT-TYPE
			SYNTAX	INTEGER
			MAX-ACCESS	read-only
			STATUS	current
			::= { hmWanMbus2F 35 }

hmWanMbus2FVIF0F		OBJECT-TYPE
			SYNTAX	INTEGER
			MAX-ACCESS	read-only
			STATUS	current
			::= { hmWanMbus2F 36 }

hmWanMbus2FValue0F		OBJECT-TYPE
			SYNTAX	INTEGER
			MAX-ACCESS	read-only
			STATUS	current
			::= { hmWanMbus2F 37 }

hmWanMbus2FVIF10		OBJECT-TYPE
			SYNTAX	INTEGER
			MAX-ACCESS	read-only
			STATUS	current
			::= { hmWanMbus2F 38 }

hmWanMbus2FValue10		OBJECT-TYPE
			SYNTAX	INTEGER
			MAX-ACCESS	read-only
			STATUS	current
			::= { hmWanMbus2F 39 }

hmWanMbus2FVIF11		OBJECT-TYPE
			SYNTAX	INTEGER
			MAX-ACCESS	read-only
			STATUS	current
			::= { hmWanMbus2F 40 }

hmWanMbus2FValue11		OBJECT-TYPE
			SYNTAX	INTEGER
			MAX-ACCESS	read-only
			STATUS	current
			::= { hmWanMbus2F 41 }

hmWanMbus2FVIF12		OBJECT-TYPE
			SYNTAX	INTEGER
			MAX-ACCESS	read-only
			STATUS	current
			::= { hmWanMbus2F 42 }

hmWanMbus2FValue12		OBJECT-TYPE
			SYNTAX	INTEGER
			MAX-ACCESS	read-only
			STATUS	current
			::= { hmWanMbus2F 43 }

hmWanMbus2FVIF13		OBJECT-TYPE
			SYNTAX	INTEGER
			MAX-ACCESS	read-only
			STATUS	current
			::= { hmWanMbus2F 44 }

hmWanMbus2FValue13		OBJECT-TYPE
			SYNTAX	INTEGER
			MAX-ACCESS	read-only
			STATUS	current
			::= { hmWanMbus2F 45 }

hmWanMbus2FVIF14		OBJECT-TYPE
			SYNTAX	INTEGER
			MAX-ACCESS	read-only
			STATUS	current
			::= { hmWanMbus2F 46 }

hmWanMbus2FValue14		OBJECT-TYPE
			SYNTAX	INTEGER
			MAX-ACCESS	read-only
			STATUS	current
			::= { hmWanMbus2F 47 }

hmWanMbus2FVIF15		OBJECT-TYPE
			SYNTAX	INTEGER
			MAX-ACCESS	read-only
			STATUS	current
			::= { hmWanMbus2F 48 }

hmWanMbus2FValue15		OBJECT-TYPE
			SYNTAX	INTEGER
			MAX-ACCESS	read-only
			STATUS	current
			::= { hmWanMbus2F 49 }

hmWanMbus2FVIF16		OBJECT-TYPE
			SYNTAX	INTEGER
			MAX-ACCESS	read-only
			STATUS	current
			::= { hmWanMbus2F 50 }

hmWanMbus2FValue16		OBJECT-TYPE
			SYNTAX	INTEGER
			MAX-ACCESS	read-only
			STATUS	current
			::= { hmWanMbus2F 51 }

hmWanMbus2FVIF17		OBJECT-TYPE
			SYNTAX	INTEGER
			MAX-ACCESS	read-only
			STATUS	current
			::= { hmWanMbus2F 52 }

hmWanMbus2FValue17		OBJECT-TYPE
			SYNTAX	INTEGER
			MAX-ACCESS	read-only
			STATUS	current
			::= { hmWanMbus2F 53 }

hmWanMbus2FVIF18		OBJECT-TYPE
			SYNTAX	INTEGER
			MAX-ACCESS	read-only
			STATUS	current
			::= { hmWanMbus2F 54 }

hmWanMbus2FValue18		OBJECT-TYPE
			SYNTAX	INTEGER
			MAX-ACCESS	read-only
			STATUS	current
			::= { hmWanMbus2F 55 }

hmWanMbus2FVIF19		OBJECT-TYPE
			SYNTAX	INTEGER
			MAX-ACCESS	read-only
			STATUS	current
			::= { hmWanMbus2F 56 }

hmWanMbus2FValue19		OBJECT-TYPE
			SYNTAX	INTEGER
			MAX-ACCESS	read-only
			STATUS	current
			::= { hmWanMbus2F 57 }

hmWanMbus2FVIF1A		OBJECT-TYPE
			SYNTAX	INTEGER
			MAX-ACCESS	read-only
			STATUS	current
			::= { hmWanMbus2F 58 }

hmWanMbus2FValue1A		OBJECT-TYPE
			SYNTAX	INTEGER
			MAX-ACCESS	read-only
			STATUS	current
			::= { hmWanMbus2F 59 }

hmWanMbus2FVIF1B		OBJECT-TYPE
			SYNTAX	INTEGER
			MAX-ACCESS	read-only
			STATUS	current
			::= { hmWanMbus2F 60 }

hmWanMbus2FValue1B		OBJECT-TYPE
			SYNTAX	INTEGER
			MAX-ACCESS	read-only
			STATUS	current
			::= { hmWanMbus2F 61 }

hmWanMbus2FVIF1C		OBJECT-TYPE
			SYNTAX	INTEGER
			MAX-ACCESS	read-only
			STATUS	current
			::= { hmWanMbus2F 62 }

hmWanMbus2FValue1C		OBJECT-TYPE
			SYNTAX	INTEGER
			MAX-ACCESS	read-only
			STATUS	current
			::= { hmWanMbus2F 63 }

hmWanMbus2FVIF1D		OBJECT-TYPE
			SYNTAX	INTEGER
			MAX-ACCESS	read-only
			STATUS	current
			::= { hmWanMbus2F 64 }

hmWanMbus2FValue1D		OBJECT-TYPE
			SYNTAX	INTEGER
			MAX-ACCESS	read-only
			STATUS	current
			::= { hmWanMbus2F 65 }

hmWanMbus2FVIF1E		OBJECT-TYPE
			SYNTAX	INTEGER
			MAX-ACCESS	read-only
			STATUS	current
			::= { hmWanMbus2F 66 }

hmWanMbus2FValue1E		OBJECT-TYPE
			SYNTAX	INTEGER
			MAX-ACCESS	read-only
			STATUS	current
			::= { hmWanMbus2F 67 }

hmWanMbus2FVIF1F		OBJECT-TYPE
			SYNTAX	INTEGER
			MAX-ACCESS	read-only
			STATUS	current
			::= { hmWanMbus2F 68 }

hmWanMbus2FValue1F		OBJECT-TYPE
			SYNTAX	INTEGER
			MAX-ACCESS	read-only
			STATUS	current
			::= { hmWanMbus2F 69 }

hmWanMbus2FVIF20		OBJECT-TYPE
			SYNTAX	INTEGER
			MAX-ACCESS	read-only
			STATUS	current
			::= { hmWanMbus2F 70 }

hmWanMbus2FValue20		OBJECT-TYPE
			SYNTAX	INTEGER
			MAX-ACCESS	read-only
			STATUS	current
			::= { hmWanMbus2F 71 }

hmWanMbus2FVIF21		OBJECT-TYPE
			SYNTAX	INTEGER
			MAX-ACCESS	read-only
			STATUS	current
			::= { hmWanMbus2F 72 }

hmWanMbus2FValue21		OBJECT-TYPE
			SYNTAX	INTEGER
			MAX-ACCESS	read-only
			STATUS	current
			::= { hmWanMbus2F 73 }

hmWanMbus2FVIF22		OBJECT-TYPE
			SYNTAX	INTEGER
			MAX-ACCESS	read-only
			STATUS	current
			::= { hmWanMbus2F 74 }

hmWanMbus2FValue22		OBJECT-TYPE
			SYNTAX	INTEGER
			MAX-ACCESS	read-only
			STATUS	current
			::= { hmWanMbus2F 75 }

hmWanMbus2FVIF23		OBJECT-TYPE
			SYNTAX	INTEGER
			MAX-ACCESS	read-only
			STATUS	current
			::= { hmWanMbus2F 76 }

hmWanMbus2FValue23		OBJECT-TYPE
			SYNTAX	INTEGER
			MAX-ACCESS	read-only
			STATUS	current
			::= { hmWanMbus2F 77 }

hmWanMbus2FVIF24		OBJECT-TYPE
			SYNTAX	INTEGER
			MAX-ACCESS	read-only
			STATUS	current
			::= { hmWanMbus2F 78 }

hmWanMbus2FValue24		OBJECT-TYPE
			SYNTAX	INTEGER
			MAX-ACCESS	read-only
			STATUS	current
			::= { hmWanMbus2F 79 }

hmWanMbus2FVIF25		OBJECT-TYPE
			SYNTAX	INTEGER
			MAX-ACCESS	read-only
			STATUS	current
			::= { hmWanMbus2F 80 }

hmWanMbus2FValue25		OBJECT-TYPE
			SYNTAX	INTEGER
			MAX-ACCESS	read-only
			STATUS	current
			::= { hmWanMbus2F 81 }

hmWanMbus2FVIF26		OBJECT-TYPE
			SYNTAX	INTEGER
			MAX-ACCESS	read-only
			STATUS	current
			::= { hmWanMbus2F 82 }

hmWanMbus2FValue26		OBJECT-TYPE
			SYNTAX	INTEGER
			MAX-ACCESS	read-only
			STATUS	current
			::= { hmWanMbus2F 83 }

hmWanMbus2FVIF27		OBJECT-TYPE
			SYNTAX	INTEGER
			MAX-ACCESS	read-only
			STATUS	current
			::= { hmWanMbus2F 84 }

hmWanMbus2FValue27		OBJECT-TYPE
			SYNTAX	INTEGER
			MAX-ACCESS	read-only
			STATUS	current
			::= { hmWanMbus2F 85 }

hmWanMbus2FVIF28		OBJECT-TYPE
			SYNTAX	INTEGER
			MAX-ACCESS	read-only
			STATUS	current
			::= { hmWanMbus2F 86 }

hmWanMbus2FValue28		OBJECT-TYPE
			SYNTAX	INTEGER
			MAX-ACCESS	read-only
			STATUS	current
			::= { hmWanMbus2F 87 }

hmWanMbus2FVIF29		OBJECT-TYPE
			SYNTAX	INTEGER
			MAX-ACCESS	read-only
			STATUS	current
			::= { hmWanMbus2F 88 }

hmWanMbus2FValue29		OBJECT-TYPE
			SYNTAX	INTEGER
			MAX-ACCESS	read-only
			STATUS	current
			::= { hmWanMbus2F 89 }

hmWanMbus2FVIF2A		OBJECT-TYPE
			SYNTAX	INTEGER
			MAX-ACCESS	read-only
			STATUS	current
			::= { hmWanMbus2F 90 }

hmWanMbus2FValue2A		OBJECT-TYPE
			SYNTAX	INTEGER
			MAX-ACCESS	read-only
			STATUS	current
			::= { hmWanMbus2F 91 }

hmWanMbus2FVIF2B		OBJECT-TYPE
			SYNTAX	INTEGER
			MAX-ACCESS	read-only
			STATUS	current
			::= { hmWanMbus2F 92 }

hmWanMbus2FValue2B		OBJECT-TYPE
			SYNTAX	INTEGER
			MAX-ACCESS	read-only
			STATUS	current
			::= { hmWanMbus2F 93 }

hmWanMbus2FVIF2C		OBJECT-TYPE
			SYNTAX	INTEGER
			MAX-ACCESS	read-only
			STATUS	current
			::= { hmWanMbus2F 94 }

hmWanMbus2FValue2C		OBJECT-TYPE
			SYNTAX	INTEGER
			MAX-ACCESS	read-only
			STATUS	current
			::= { hmWanMbus2F 95 }

hmWanMbus2FVIF2D		OBJECT-TYPE
			SYNTAX	INTEGER
			MAX-ACCESS	read-only
			STATUS	current
			::= { hmWanMbus2F 96 }

hmWanMbus2FValue2D		OBJECT-TYPE
			SYNTAX	INTEGER
			MAX-ACCESS	read-only
			STATUS	current
			::= { hmWanMbus2F 97 }

hmWanMbus2FVIF2E		OBJECT-TYPE
			SYNTAX	INTEGER
			MAX-ACCESS	read-only
			STATUS	current
			::= { hmWanMbus2F 98 }

hmWanMbus2FValue2E		OBJECT-TYPE
			SYNTAX	INTEGER
			MAX-ACCESS	read-only
			STATUS	current
			::= { hmWanMbus2F 99 }

hmWanMbus2FVIF2F		OBJECT-TYPE
			SYNTAX	INTEGER
			MAX-ACCESS	read-only
			STATUS	current
			::= { hmWanMbus2F 100 }

hmWanMbus2FValue2F		OBJECT-TYPE
			SYNTAX	INTEGER
			MAX-ACCESS	read-only
			STATUS	current
			::= { hmWanMbus2F 101 }

hmWanMbus30			OBJECT IDENTIFIER ::= { hmWanMbus 48 }

hmWanMbus30IdNumber		OBJECT-TYPE
			SYNTAX	Gauge32
			MAX-ACCESS	read-only
			STATUS	current
			::= { hmWanMbus30 1 }

hmWanMbus30Manufacturer	OBJECT-TYPE
			SYNTAX	Gauge32
			MAX-ACCESS	read-only
			STATUS	current
			::= { hmWanMbus30 2 }

hmWanMbus30Version		OBJECT-TYPE
			SYNTAX	Gauge32
			MAX-ACCESS	read-only
			STATUS	current
			::= { hmWanMbus30 3 }

hmWanMbus30Medium		OBJECT-TYPE
			SYNTAX	Gauge32
			MAX-ACCESS	read-only
			STATUS	current
			::= { hmWanMbus30 4 }

hmWanMbus30Status		OBJECT-TYPE
			SYNTAX	Gauge32
			MAX-ACCESS	read-only
			STATUS	current
			::= { hmWanMbus30 5 }

hmWanMbus30VIF00		OBJECT-TYPE
			SYNTAX	INTEGER
			MAX-ACCESS	read-only
			STATUS	current
			::= { hmWanMbus30 6 }

hmWanMbus30Value00		OBJECT-TYPE
			SYNTAX	INTEGER
			MAX-ACCESS	read-only
			STATUS	current
			::= { hmWanMbus30 7 }

hmWanMbus30VIF01		OBJECT-TYPE
			SYNTAX	INTEGER
			MAX-ACCESS	read-only
			STATUS	current
			::= { hmWanMbus30 8 }

hmWanMbus30Value01		OBJECT-TYPE
			SYNTAX	INTEGER
			MAX-ACCESS	read-only
			STATUS	current
			::= { hmWanMbus30 9 }

hmWanMbus30VIF02		OBJECT-TYPE
			SYNTAX	INTEGER
			MAX-ACCESS	read-only
			STATUS	current
			::= { hmWanMbus30 10 }

hmWanMbus30Value02		OBJECT-TYPE
			SYNTAX	INTEGER
			MAX-ACCESS	read-only
			STATUS	current
			::= { hmWanMbus30 11 }

hmWanMbus30VIF03		OBJECT-TYPE
			SYNTAX	INTEGER
			MAX-ACCESS	read-only
			STATUS	current
			::= { hmWanMbus30 12 }

hmWanMbus30Value03		OBJECT-TYPE
			SYNTAX	INTEGER
			MAX-ACCESS	read-only
			STATUS	current
			::= { hmWanMbus30 13 }

hmWanMbus30VIF04		OBJECT-TYPE
			SYNTAX	INTEGER
			MAX-ACCESS	read-only
			STATUS	current
			::= { hmWanMbus30 14 }

hmWanMbus30Value04		OBJECT-TYPE
			SYNTAX	INTEGER
			MAX-ACCESS	read-only
			STATUS	current
			::= { hmWanMbus30 15 }

hmWanMbus30VIF05		OBJECT-TYPE
			SYNTAX	INTEGER
			MAX-ACCESS	read-only
			STATUS	current
			::= { hmWanMbus30 16 }

hmWanMbus30Value05		OBJECT-TYPE
			SYNTAX	INTEGER
			MAX-ACCESS	read-only
			STATUS	current
			::= { hmWanMbus30 17 }

hmWanMbus30VIF06		OBJECT-TYPE
			SYNTAX	INTEGER
			MAX-ACCESS	read-only
			STATUS	current
			::= { hmWanMbus30 18 }

hmWanMbus30Value06		OBJECT-TYPE
			SYNTAX	INTEGER
			MAX-ACCESS	read-only
			STATUS	current
			::= { hmWanMbus30 19 }

hmWanMbus30VIF07		OBJECT-TYPE
			SYNTAX	INTEGER
			MAX-ACCESS	read-only
			STATUS	current
			::= { hmWanMbus30 20 }

hmWanMbus30Value07		OBJECT-TYPE
			SYNTAX	INTEGER
			MAX-ACCESS	read-only
			STATUS	current
			::= { hmWanMbus30 21 }

hmWanMbus30VIF08		OBJECT-TYPE
			SYNTAX	INTEGER
			MAX-ACCESS	read-only
			STATUS	current
			::= { hmWanMbus30 22 }

hmWanMbus30Value08		OBJECT-TYPE
			SYNTAX	INTEGER
			MAX-ACCESS	read-only
			STATUS	current
			::= { hmWanMbus30 23 }

hmWanMbus30VIF09		OBJECT-TYPE
			SYNTAX	INTEGER
			MAX-ACCESS	read-only
			STATUS	current
			::= { hmWanMbus30 24 }

hmWanMbus30Value09		OBJECT-TYPE
			SYNTAX	INTEGER
			MAX-ACCESS	read-only
			STATUS	current
			::= { hmWanMbus30 25 }

hmWanMbus30VIF0A		OBJECT-TYPE
			SYNTAX	INTEGER
			MAX-ACCESS	read-only
			STATUS	current
			::= { hmWanMbus30 26 }

hmWanMbus30Value0A		OBJECT-TYPE
			SYNTAX	INTEGER
			MAX-ACCESS	read-only
			STATUS	current
			::= { hmWanMbus30 27 }

hmWanMbus30VIF0B		OBJECT-TYPE
			SYNTAX	INTEGER
			MAX-ACCESS	read-only
			STATUS	current
			::= { hmWanMbus30 28 }

hmWanMbus30Value0B		OBJECT-TYPE
			SYNTAX	INTEGER
			MAX-ACCESS	read-only
			STATUS	current
			::= { hmWanMbus30 29 }

hmWanMbus30VIF0C		OBJECT-TYPE
			SYNTAX	INTEGER
			MAX-ACCESS	read-only
			STATUS	current
			::= { hmWanMbus30 30 }

hmWanMbus30Value0C		OBJECT-TYPE
			SYNTAX	INTEGER
			MAX-ACCESS	read-only
			STATUS	current
			::= { hmWanMbus30 31 }

hmWanMbus30VIF0D		OBJECT-TYPE
			SYNTAX	INTEGER
			MAX-ACCESS	read-only
			STATUS	current
			::= { hmWanMbus30 32 }

hmWanMbus30Value0D		OBJECT-TYPE
			SYNTAX	INTEGER
			MAX-ACCESS	read-only
			STATUS	current
			::= { hmWanMbus30 33 }

hmWanMbus30VIF0E		OBJECT-TYPE
			SYNTAX	INTEGER
			MAX-ACCESS	read-only
			STATUS	current
			::= { hmWanMbus30 34 }

hmWanMbus30Value0E		OBJECT-TYPE
			SYNTAX	INTEGER
			MAX-ACCESS	read-only
			STATUS	current
			::= { hmWanMbus30 35 }

hmWanMbus30VIF0F		OBJECT-TYPE
			SYNTAX	INTEGER
			MAX-ACCESS	read-only
			STATUS	current
			::= { hmWanMbus30 36 }

hmWanMbus30Value0F		OBJECT-TYPE
			SYNTAX	INTEGER
			MAX-ACCESS	read-only
			STATUS	current
			::= { hmWanMbus30 37 }

hmWanMbus30VIF10		OBJECT-TYPE
			SYNTAX	INTEGER
			MAX-ACCESS	read-only
			STATUS	current
			::= { hmWanMbus30 38 }

hmWanMbus30Value10		OBJECT-TYPE
			SYNTAX	INTEGER
			MAX-ACCESS	read-only
			STATUS	current
			::= { hmWanMbus30 39 }

hmWanMbus30VIF11		OBJECT-TYPE
			SYNTAX	INTEGER
			MAX-ACCESS	read-only
			STATUS	current
			::= { hmWanMbus30 40 }

hmWanMbus30Value11		OBJECT-TYPE
			SYNTAX	INTEGER
			MAX-ACCESS	read-only
			STATUS	current
			::= { hmWanMbus30 41 }

hmWanMbus30VIF12		OBJECT-TYPE
			SYNTAX	INTEGER
			MAX-ACCESS	read-only
			STATUS	current
			::= { hmWanMbus30 42 }

hmWanMbus30Value12		OBJECT-TYPE
			SYNTAX	INTEGER
			MAX-ACCESS	read-only
			STATUS	current
			::= { hmWanMbus30 43 }

hmWanMbus30VIF13		OBJECT-TYPE
			SYNTAX	INTEGER
			MAX-ACCESS	read-only
			STATUS	current
			::= { hmWanMbus30 44 }

hmWanMbus30Value13		OBJECT-TYPE
			SYNTAX	INTEGER
			MAX-ACCESS	read-only
			STATUS	current
			::= { hmWanMbus30 45 }

hmWanMbus30VIF14		OBJECT-TYPE
			SYNTAX	INTEGER
			MAX-ACCESS	read-only
			STATUS	current
			::= { hmWanMbus30 46 }

hmWanMbus30Value14		OBJECT-TYPE
			SYNTAX	INTEGER
			MAX-ACCESS	read-only
			STATUS	current
			::= { hmWanMbus30 47 }

hmWanMbus30VIF15		OBJECT-TYPE
			SYNTAX	INTEGER
			MAX-ACCESS	read-only
			STATUS	current
			::= { hmWanMbus30 48 }

hmWanMbus30Value15		OBJECT-TYPE
			SYNTAX	INTEGER
			MAX-ACCESS	read-only
			STATUS	current
			::= { hmWanMbus30 49 }

hmWanMbus30VIF16		OBJECT-TYPE
			SYNTAX	INTEGER
			MAX-ACCESS	read-only
			STATUS	current
			::= { hmWanMbus30 50 }

hmWanMbus30Value16		OBJECT-TYPE
			SYNTAX	INTEGER
			MAX-ACCESS	read-only
			STATUS	current
			::= { hmWanMbus30 51 }

hmWanMbus30VIF17		OBJECT-TYPE
			SYNTAX	INTEGER
			MAX-ACCESS	read-only
			STATUS	current
			::= { hmWanMbus30 52 }

hmWanMbus30Value17		OBJECT-TYPE
			SYNTAX	INTEGER
			MAX-ACCESS	read-only
			STATUS	current
			::= { hmWanMbus30 53 }

hmWanMbus30VIF18		OBJECT-TYPE
			SYNTAX	INTEGER
			MAX-ACCESS	read-only
			STATUS	current
			::= { hmWanMbus30 54 }

hmWanMbus30Value18		OBJECT-TYPE
			SYNTAX	INTEGER
			MAX-ACCESS	read-only
			STATUS	current
			::= { hmWanMbus30 55 }

hmWanMbus30VIF19		OBJECT-TYPE
			SYNTAX	INTEGER
			MAX-ACCESS	read-only
			STATUS	current
			::= { hmWanMbus30 56 }

hmWanMbus30Value19		OBJECT-TYPE
			SYNTAX	INTEGER
			MAX-ACCESS	read-only
			STATUS	current
			::= { hmWanMbus30 57 }

hmWanMbus30VIF1A		OBJECT-TYPE
			SYNTAX	INTEGER
			MAX-ACCESS	read-only
			STATUS	current
			::= { hmWanMbus30 58 }

hmWanMbus30Value1A		OBJECT-TYPE
			SYNTAX	INTEGER
			MAX-ACCESS	read-only
			STATUS	current
			::= { hmWanMbus30 59 }

hmWanMbus30VIF1B		OBJECT-TYPE
			SYNTAX	INTEGER
			MAX-ACCESS	read-only
			STATUS	current
			::= { hmWanMbus30 60 }

hmWanMbus30Value1B		OBJECT-TYPE
			SYNTAX	INTEGER
			MAX-ACCESS	read-only
			STATUS	current
			::= { hmWanMbus30 61 }

hmWanMbus30VIF1C		OBJECT-TYPE
			SYNTAX	INTEGER
			MAX-ACCESS	read-only
			STATUS	current
			::= { hmWanMbus30 62 }

hmWanMbus30Value1C		OBJECT-TYPE
			SYNTAX	INTEGER
			MAX-ACCESS	read-only
			STATUS	current
			::= { hmWanMbus30 63 }

hmWanMbus30VIF1D		OBJECT-TYPE
			SYNTAX	INTEGER
			MAX-ACCESS	read-only
			STATUS	current
			::= { hmWanMbus30 64 }

hmWanMbus30Value1D		OBJECT-TYPE
			SYNTAX	INTEGER
			MAX-ACCESS	read-only
			STATUS	current
			::= { hmWanMbus30 65 }

hmWanMbus30VIF1E		OBJECT-TYPE
			SYNTAX	INTEGER
			MAX-ACCESS	read-only
			STATUS	current
			::= { hmWanMbus30 66 }

hmWanMbus30Value1E		OBJECT-TYPE
			SYNTAX	INTEGER
			MAX-ACCESS	read-only
			STATUS	current
			::= { hmWanMbus30 67 }

hmWanMbus30VIF1F		OBJECT-TYPE
			SYNTAX	INTEGER
			MAX-ACCESS	read-only
			STATUS	current
			::= { hmWanMbus30 68 }

hmWanMbus30Value1F		OBJECT-TYPE
			SYNTAX	INTEGER
			MAX-ACCESS	read-only
			STATUS	current
			::= { hmWanMbus30 69 }

hmWanMbus30VIF20		OBJECT-TYPE
			SYNTAX	INTEGER
			MAX-ACCESS	read-only
			STATUS	current
			::= { hmWanMbus30 70 }

hmWanMbus30Value20		OBJECT-TYPE
			SYNTAX	INTEGER
			MAX-ACCESS	read-only
			STATUS	current
			::= { hmWanMbus30 71 }

hmWanMbus30VIF21		OBJECT-TYPE
			SYNTAX	INTEGER
			MAX-ACCESS	read-only
			STATUS	current
			::= { hmWanMbus30 72 }

hmWanMbus30Value21		OBJECT-TYPE
			SYNTAX	INTEGER
			MAX-ACCESS	read-only
			STATUS	current
			::= { hmWanMbus30 73 }

hmWanMbus30VIF22		OBJECT-TYPE
			SYNTAX	INTEGER
			MAX-ACCESS	read-only
			STATUS	current
			::= { hmWanMbus30 74 }

hmWanMbus30Value22		OBJECT-TYPE
			SYNTAX	INTEGER
			MAX-ACCESS	read-only
			STATUS	current
			::= { hmWanMbus30 75 }

hmWanMbus30VIF23		OBJECT-TYPE
			SYNTAX	INTEGER
			MAX-ACCESS	read-only
			STATUS	current
			::= { hmWanMbus30 76 }

hmWanMbus30Value23		OBJECT-TYPE
			SYNTAX	INTEGER
			MAX-ACCESS	read-only
			STATUS	current
			::= { hmWanMbus30 77 }

hmWanMbus30VIF24		OBJECT-TYPE
			SYNTAX	INTEGER
			MAX-ACCESS	read-only
			STATUS	current
			::= { hmWanMbus30 78 }

hmWanMbus30Value24		OBJECT-TYPE
			SYNTAX	INTEGER
			MAX-ACCESS	read-only
			STATUS	current
			::= { hmWanMbus30 79 }

hmWanMbus30VIF25		OBJECT-TYPE
			SYNTAX	INTEGER
			MAX-ACCESS	read-only
			STATUS	current
			::= { hmWanMbus30 80 }

hmWanMbus30Value25		OBJECT-TYPE
			SYNTAX	INTEGER
			MAX-ACCESS	read-only
			STATUS	current
			::= { hmWanMbus30 81 }

hmWanMbus30VIF26		OBJECT-TYPE
			SYNTAX	INTEGER
			MAX-ACCESS	read-only
			STATUS	current
			::= { hmWanMbus30 82 }

hmWanMbus30Value26		OBJECT-TYPE
			SYNTAX	INTEGER
			MAX-ACCESS	read-only
			STATUS	current
			::= { hmWanMbus30 83 }

hmWanMbus30VIF27		OBJECT-TYPE
			SYNTAX	INTEGER
			MAX-ACCESS	read-only
			STATUS	current
			::= { hmWanMbus30 84 }

hmWanMbus30Value27		OBJECT-TYPE
			SYNTAX	INTEGER
			MAX-ACCESS	read-only
			STATUS	current
			::= { hmWanMbus30 85 }

hmWanMbus30VIF28		OBJECT-TYPE
			SYNTAX	INTEGER
			MAX-ACCESS	read-only
			STATUS	current
			::= { hmWanMbus30 86 }

hmWanMbus30Value28		OBJECT-TYPE
			SYNTAX	INTEGER
			MAX-ACCESS	read-only
			STATUS	current
			::= { hmWanMbus30 87 }

hmWanMbus30VIF29		OBJECT-TYPE
			SYNTAX	INTEGER
			MAX-ACCESS	read-only
			STATUS	current
			::= { hmWanMbus30 88 }

hmWanMbus30Value29		OBJECT-TYPE
			SYNTAX	INTEGER
			MAX-ACCESS	read-only
			STATUS	current
			::= { hmWanMbus30 89 }

hmWanMbus30VIF2A		OBJECT-TYPE
			SYNTAX	INTEGER
			MAX-ACCESS	read-only
			STATUS	current
			::= { hmWanMbus30 90 }

hmWanMbus30Value2A		OBJECT-TYPE
			SYNTAX	INTEGER
			MAX-ACCESS	read-only
			STATUS	current
			::= { hmWanMbus30 91 }

hmWanMbus30VIF2B		OBJECT-TYPE
			SYNTAX	INTEGER
			MAX-ACCESS	read-only
			STATUS	current
			::= { hmWanMbus30 92 }

hmWanMbus30Value2B		OBJECT-TYPE
			SYNTAX	INTEGER
			MAX-ACCESS	read-only
			STATUS	current
			::= { hmWanMbus30 93 }

hmWanMbus30VIF2C		OBJECT-TYPE
			SYNTAX	INTEGER
			MAX-ACCESS	read-only
			STATUS	current
			::= { hmWanMbus30 94 }

hmWanMbus30Value2C		OBJECT-TYPE
			SYNTAX	INTEGER
			MAX-ACCESS	read-only
			STATUS	current
			::= { hmWanMbus30 95 }

hmWanMbus30VIF2D		OBJECT-TYPE
			SYNTAX	INTEGER
			MAX-ACCESS	read-only
			STATUS	current
			::= { hmWanMbus30 96 }

hmWanMbus30Value2D		OBJECT-TYPE
			SYNTAX	INTEGER
			MAX-ACCESS	read-only
			STATUS	current
			::= { hmWanMbus30 97 }

hmWanMbus30VIF2E		OBJECT-TYPE
			SYNTAX	INTEGER
			MAX-ACCESS	read-only
			STATUS	current
			::= { hmWanMbus30 98 }

hmWanMbus30Value2E		OBJECT-TYPE
			SYNTAX	INTEGER
			MAX-ACCESS	read-only
			STATUS	current
			::= { hmWanMbus30 99 }

hmWanMbus30VIF2F		OBJECT-TYPE
			SYNTAX	INTEGER
			MAX-ACCESS	read-only
			STATUS	current
			::= { hmWanMbus30 100 }

hmWanMbus30Value2F		OBJECT-TYPE
			SYNTAX	INTEGER
			MAX-ACCESS	read-only
			STATUS	current
			::= { hmWanMbus30 101 }

hmWanMbus31			OBJECT IDENTIFIER ::= { hmWanMbus 49 }

hmWanMbus31IdNumber		OBJECT-TYPE
			SYNTAX	Gauge32
			MAX-ACCESS	read-only
			STATUS	current
			::= { hmWanMbus31 1 }

hmWanMbus31Manufacturer	OBJECT-TYPE
			SYNTAX	Gauge32
			MAX-ACCESS	read-only
			STATUS	current
			::= { hmWanMbus31 2 }

hmWanMbus31Version		OBJECT-TYPE
			SYNTAX	Gauge32
			MAX-ACCESS	read-only
			STATUS	current
			::= { hmWanMbus31 3 }

hmWanMbus31Medium		OBJECT-TYPE
			SYNTAX	Gauge32
			MAX-ACCESS	read-only
			STATUS	current
			::= { hmWanMbus31 4 }

hmWanMbus31Status		OBJECT-TYPE
			SYNTAX	Gauge32
			MAX-ACCESS	read-only
			STATUS	current
			::= { hmWanMbus31 5 }

hmWanMbus31VIF00		OBJECT-TYPE
			SYNTAX	INTEGER
			MAX-ACCESS	read-only
			STATUS	current
			::= { hmWanMbus31 6 }

hmWanMbus31Value00		OBJECT-TYPE
			SYNTAX	INTEGER
			MAX-ACCESS	read-only
			STATUS	current
			::= { hmWanMbus31 7 }

hmWanMbus31VIF01		OBJECT-TYPE
			SYNTAX	INTEGER
			MAX-ACCESS	read-only
			STATUS	current
			::= { hmWanMbus31 8 }

hmWanMbus31Value01		OBJECT-TYPE
			SYNTAX	INTEGER
			MAX-ACCESS	read-only
			STATUS	current
			::= { hmWanMbus31 9 }

hmWanMbus31VIF02		OBJECT-TYPE
			SYNTAX	INTEGER
			MAX-ACCESS	read-only
			STATUS	current
			::= { hmWanMbus31 10 }

hmWanMbus31Value02		OBJECT-TYPE
			SYNTAX	INTEGER
			MAX-ACCESS	read-only
			STATUS	current
			::= { hmWanMbus31 11 }

hmWanMbus31VIF03		OBJECT-TYPE
			SYNTAX	INTEGER
			MAX-ACCESS	read-only
			STATUS	current
			::= { hmWanMbus31 12 }

hmWanMbus31Value03		OBJECT-TYPE
			SYNTAX	INTEGER
			MAX-ACCESS	read-only
			STATUS	current
			::= { hmWanMbus31 13 }

hmWanMbus31VIF04		OBJECT-TYPE
			SYNTAX	INTEGER
			MAX-ACCESS	read-only
			STATUS	current
			::= { hmWanMbus31 14 }

hmWanMbus31Value04		OBJECT-TYPE
			SYNTAX	INTEGER
			MAX-ACCESS	read-only
			STATUS	current
			::= { hmWanMbus31 15 }

hmWanMbus31VIF05		OBJECT-TYPE
			SYNTAX	INTEGER
			MAX-ACCESS	read-only
			STATUS	current
			::= { hmWanMbus31 16 }

hmWanMbus31Value05		OBJECT-TYPE
			SYNTAX	INTEGER
			MAX-ACCESS	read-only
			STATUS	current
			::= { hmWanMbus31 17 }

hmWanMbus31VIF06		OBJECT-TYPE
			SYNTAX	INTEGER
			MAX-ACCESS	read-only
			STATUS	current
			::= { hmWanMbus31 18 }

hmWanMbus31Value06		OBJECT-TYPE
			SYNTAX	INTEGER
			MAX-ACCESS	read-only
			STATUS	current
			::= { hmWanMbus31 19 }

hmWanMbus31VIF07		OBJECT-TYPE
			SYNTAX	INTEGER
			MAX-ACCESS	read-only
			STATUS	current
			::= { hmWanMbus31 20 }

hmWanMbus31Value07		OBJECT-TYPE
			SYNTAX	INTEGER
			MAX-ACCESS	read-only
			STATUS	current
			::= { hmWanMbus31 21 }

hmWanMbus31VIF08		OBJECT-TYPE
			SYNTAX	INTEGER
			MAX-ACCESS	read-only
			STATUS	current
			::= { hmWanMbus31 22 }

hmWanMbus31Value08		OBJECT-TYPE
			SYNTAX	INTEGER
			MAX-ACCESS	read-only
			STATUS	current
			::= { hmWanMbus31 23 }

hmWanMbus31VIF09		OBJECT-TYPE
			SYNTAX	INTEGER
			MAX-ACCESS	read-only
			STATUS	current
			::= { hmWanMbus31 24 }

hmWanMbus31Value09		OBJECT-TYPE
			SYNTAX	INTEGER
			MAX-ACCESS	read-only
			STATUS	current
			::= { hmWanMbus31 25 }

hmWanMbus31VIF0A		OBJECT-TYPE
			SYNTAX	INTEGER
			MAX-ACCESS	read-only
			STATUS	current
			::= { hmWanMbus31 26 }

hmWanMbus31Value0A		OBJECT-TYPE
			SYNTAX	INTEGER
			MAX-ACCESS	read-only
			STATUS	current
			::= { hmWanMbus31 27 }

hmWanMbus31VIF0B		OBJECT-TYPE
			SYNTAX	INTEGER
			MAX-ACCESS	read-only
			STATUS	current
			::= { hmWanMbus31 28 }

hmWanMbus31Value0B		OBJECT-TYPE
			SYNTAX	INTEGER
			MAX-ACCESS	read-only
			STATUS	current
			::= { hmWanMbus31 29 }

hmWanMbus31VIF0C		OBJECT-TYPE
			SYNTAX	INTEGER
			MAX-ACCESS	read-only
			STATUS	current
			::= { hmWanMbus31 30 }

hmWanMbus31Value0C		OBJECT-TYPE
			SYNTAX	INTEGER
			MAX-ACCESS	read-only
			STATUS	current
			::= { hmWanMbus31 31 }

hmWanMbus31VIF0D		OBJECT-TYPE
			SYNTAX	INTEGER
			MAX-ACCESS	read-only
			STATUS	current
			::= { hmWanMbus31 32 }

hmWanMbus31Value0D		OBJECT-TYPE
			SYNTAX	INTEGER
			MAX-ACCESS	read-only
			STATUS	current
			::= { hmWanMbus31 33 }

hmWanMbus31VIF0E		OBJECT-TYPE
			SYNTAX	INTEGER
			MAX-ACCESS	read-only
			STATUS	current
			::= { hmWanMbus31 34 }

hmWanMbus31Value0E		OBJECT-TYPE
			SYNTAX	INTEGER
			MAX-ACCESS	read-only
			STATUS	current
			::= { hmWanMbus31 35 }

hmWanMbus31VIF0F		OBJECT-TYPE
			SYNTAX	INTEGER
			MAX-ACCESS	read-only
			STATUS	current
			::= { hmWanMbus31 36 }

hmWanMbus31Value0F		OBJECT-TYPE
			SYNTAX	INTEGER
			MAX-ACCESS	read-only
			STATUS	current
			::= { hmWanMbus31 37 }

hmWanMbus31VIF10		OBJECT-TYPE
			SYNTAX	INTEGER
			MAX-ACCESS	read-only
			STATUS	current
			::= { hmWanMbus31 38 }

hmWanMbus31Value10		OBJECT-TYPE
			SYNTAX	INTEGER
			MAX-ACCESS	read-only
			STATUS	current
			::= { hmWanMbus31 39 }

hmWanMbus31VIF11		OBJECT-TYPE
			SYNTAX	INTEGER
			MAX-ACCESS	read-only
			STATUS	current
			::= { hmWanMbus31 40 }

hmWanMbus31Value11		OBJECT-TYPE
			SYNTAX	INTEGER
			MAX-ACCESS	read-only
			STATUS	current
			::= { hmWanMbus31 41 }

hmWanMbus31VIF12		OBJECT-TYPE
			SYNTAX	INTEGER
			MAX-ACCESS	read-only
			STATUS	current
			::= { hmWanMbus31 42 }

hmWanMbus31Value12		OBJECT-TYPE
			SYNTAX	INTEGER
			MAX-ACCESS	read-only
			STATUS	current
			::= { hmWanMbus31 43 }

hmWanMbus31VIF13		OBJECT-TYPE
			SYNTAX	INTEGER
			MAX-ACCESS	read-only
			STATUS	current
			::= { hmWanMbus31 44 }

hmWanMbus31Value13		OBJECT-TYPE
			SYNTAX	INTEGER
			MAX-ACCESS	read-only
			STATUS	current
			::= { hmWanMbus31 45 }

hmWanMbus31VIF14		OBJECT-TYPE
			SYNTAX	INTEGER
			MAX-ACCESS	read-only
			STATUS	current
			::= { hmWanMbus31 46 }

hmWanMbus31Value14		OBJECT-TYPE
			SYNTAX	INTEGER
			MAX-ACCESS	read-only
			STATUS	current
			::= { hmWanMbus31 47 }

hmWanMbus31VIF15		OBJECT-TYPE
			SYNTAX	INTEGER
			MAX-ACCESS	read-only
			STATUS	current
			::= { hmWanMbus31 48 }

hmWanMbus31Value15		OBJECT-TYPE
			SYNTAX	INTEGER
			MAX-ACCESS	read-only
			STATUS	current
			::= { hmWanMbus31 49 }

hmWanMbus31VIF16		OBJECT-TYPE
			SYNTAX	INTEGER
			MAX-ACCESS	read-only
			STATUS	current
			::= { hmWanMbus31 50 }

hmWanMbus31Value16		OBJECT-TYPE
			SYNTAX	INTEGER
			MAX-ACCESS	read-only
			STATUS	current
			::= { hmWanMbus31 51 }

hmWanMbus31VIF17		OBJECT-TYPE
			SYNTAX	INTEGER
			MAX-ACCESS	read-only
			STATUS	current
			::= { hmWanMbus31 52 }

hmWanMbus31Value17		OBJECT-TYPE
			SYNTAX	INTEGER
			MAX-ACCESS	read-only
			STATUS	current
			::= { hmWanMbus31 53 }

hmWanMbus31VIF18		OBJECT-TYPE
			SYNTAX	INTEGER
			MAX-ACCESS	read-only
			STATUS	current
			::= { hmWanMbus31 54 }

hmWanMbus31Value18		OBJECT-TYPE
			SYNTAX	INTEGER
			MAX-ACCESS	read-only
			STATUS	current
			::= { hmWanMbus31 55 }

hmWanMbus31VIF19		OBJECT-TYPE
			SYNTAX	INTEGER
			MAX-ACCESS	read-only
			STATUS	current
			::= { hmWanMbus31 56 }

hmWanMbus31Value19		OBJECT-TYPE
			SYNTAX	INTEGER
			MAX-ACCESS	read-only
			STATUS	current
			::= { hmWanMbus31 57 }

hmWanMbus31VIF1A		OBJECT-TYPE
			SYNTAX	INTEGER
			MAX-ACCESS	read-only
			STATUS	current
			::= { hmWanMbus31 58 }

hmWanMbus31Value1A		OBJECT-TYPE
			SYNTAX	INTEGER
			MAX-ACCESS	read-only
			STATUS	current
			::= { hmWanMbus31 59 }

hmWanMbus31VIF1B		OBJECT-TYPE
			SYNTAX	INTEGER
			MAX-ACCESS	read-only
			STATUS	current
			::= { hmWanMbus31 60 }

hmWanMbus31Value1B		OBJECT-TYPE
			SYNTAX	INTEGER
			MAX-ACCESS	read-only
			STATUS	current
			::= { hmWanMbus31 61 }

hmWanMbus31VIF1C		OBJECT-TYPE
			SYNTAX	INTEGER
			MAX-ACCESS	read-only
			STATUS	current
			::= { hmWanMbus31 62 }

hmWanMbus31Value1C		OBJECT-TYPE
			SYNTAX	INTEGER
			MAX-ACCESS	read-only
			STATUS	current
			::= { hmWanMbus31 63 }

hmWanMbus31VIF1D		OBJECT-TYPE
			SYNTAX	INTEGER
			MAX-ACCESS	read-only
			STATUS	current
			::= { hmWanMbus31 64 }

hmWanMbus31Value1D		OBJECT-TYPE
			SYNTAX	INTEGER
			MAX-ACCESS	read-only
			STATUS	current
			::= { hmWanMbus31 65 }

hmWanMbus31VIF1E		OBJECT-TYPE
			SYNTAX	INTEGER
			MAX-ACCESS	read-only
			STATUS	current
			::= { hmWanMbus31 66 }

hmWanMbus31Value1E		OBJECT-TYPE
			SYNTAX	INTEGER
			MAX-ACCESS	read-only
			STATUS	current
			::= { hmWanMbus31 67 }

hmWanMbus31VIF1F		OBJECT-TYPE
			SYNTAX	INTEGER
			MAX-ACCESS	read-only
			STATUS	current
			::= { hmWanMbus31 68 }

hmWanMbus31Value1F		OBJECT-TYPE
			SYNTAX	INTEGER
			MAX-ACCESS	read-only
			STATUS	current
			::= { hmWanMbus31 69 }

hmWanMbus31VIF20		OBJECT-TYPE
			SYNTAX	INTEGER
			MAX-ACCESS	read-only
			STATUS	current
			::= { hmWanMbus31 70 }

hmWanMbus31Value20		OBJECT-TYPE
			SYNTAX	INTEGER
			MAX-ACCESS	read-only
			STATUS	current
			::= { hmWanMbus31 71 }

hmWanMbus31VIF21		OBJECT-TYPE
			SYNTAX	INTEGER
			MAX-ACCESS	read-only
			STATUS	current
			::= { hmWanMbus31 72 }

hmWanMbus31Value21		OBJECT-TYPE
			SYNTAX	INTEGER
			MAX-ACCESS	read-only
			STATUS	current
			::= { hmWanMbus31 73 }

hmWanMbus31VIF22		OBJECT-TYPE
			SYNTAX	INTEGER
			MAX-ACCESS	read-only
			STATUS	current
			::= { hmWanMbus31 74 }

hmWanMbus31Value22		OBJECT-TYPE
			SYNTAX	INTEGER
			MAX-ACCESS	read-only
			STATUS	current
			::= { hmWanMbus31 75 }

hmWanMbus31VIF23		OBJECT-TYPE
			SYNTAX	INTEGER
			MAX-ACCESS	read-only
			STATUS	current
			::= { hmWanMbus31 76 }

hmWanMbus31Value23		OBJECT-TYPE
			SYNTAX	INTEGER
			MAX-ACCESS	read-only
			STATUS	current
			::= { hmWanMbus31 77 }

hmWanMbus31VIF24		OBJECT-TYPE
			SYNTAX	INTEGER
			MAX-ACCESS	read-only
			STATUS	current
			::= { hmWanMbus31 78 }

hmWanMbus31Value24		OBJECT-TYPE
			SYNTAX	INTEGER
			MAX-ACCESS	read-only
			STATUS	current
			::= { hmWanMbus31 79 }

hmWanMbus31VIF25		OBJECT-TYPE
			SYNTAX	INTEGER
			MAX-ACCESS	read-only
			STATUS	current
			::= { hmWanMbus31 80 }

hmWanMbus31Value25		OBJECT-TYPE
			SYNTAX	INTEGER
			MAX-ACCESS	read-only
			STATUS	current
			::= { hmWanMbus31 81 }

hmWanMbus31VIF26		OBJECT-TYPE
			SYNTAX	INTEGER
			MAX-ACCESS	read-only
			STATUS	current
			::= { hmWanMbus31 82 }

hmWanMbus31Value26		OBJECT-TYPE
			SYNTAX	INTEGER
			MAX-ACCESS	read-only
			STATUS	current
			::= { hmWanMbus31 83 }

hmWanMbus31VIF27		OBJECT-TYPE
			SYNTAX	INTEGER
			MAX-ACCESS	read-only
			STATUS	current
			::= { hmWanMbus31 84 }

hmWanMbus31Value27		OBJECT-TYPE
			SYNTAX	INTEGER
			MAX-ACCESS	read-only
			STATUS	current
			::= { hmWanMbus31 85 }

hmWanMbus31VIF28		OBJECT-TYPE
			SYNTAX	INTEGER
			MAX-ACCESS	read-only
			STATUS	current
			::= { hmWanMbus31 86 }

hmWanMbus31Value28		OBJECT-TYPE
			SYNTAX	INTEGER
			MAX-ACCESS	read-only
			STATUS	current
			::= { hmWanMbus31 87 }

hmWanMbus31VIF29		OBJECT-TYPE
			SYNTAX	INTEGER
			MAX-ACCESS	read-only
			STATUS	current
			::= { hmWanMbus31 88 }

hmWanMbus31Value29		OBJECT-TYPE
			SYNTAX	INTEGER
			MAX-ACCESS	read-only
			STATUS	current
			::= { hmWanMbus31 89 }

hmWanMbus31VIF2A		OBJECT-TYPE
			SYNTAX	INTEGER
			MAX-ACCESS	read-only
			STATUS	current
			::= { hmWanMbus31 90 }

hmWanMbus31Value2A		OBJECT-TYPE
			SYNTAX	INTEGER
			MAX-ACCESS	read-only
			STATUS	current
			::= { hmWanMbus31 91 }

hmWanMbus31VIF2B		OBJECT-TYPE
			SYNTAX	INTEGER
			MAX-ACCESS	read-only
			STATUS	current
			::= { hmWanMbus31 92 }

hmWanMbus31Value2B		OBJECT-TYPE
			SYNTAX	INTEGER
			MAX-ACCESS	read-only
			STATUS	current
			::= { hmWanMbus31 93 }

hmWanMbus31VIF2C		OBJECT-TYPE
			SYNTAX	INTEGER
			MAX-ACCESS	read-only
			STATUS	current
			::= { hmWanMbus31 94 }

hmWanMbus31Value2C		OBJECT-TYPE
			SYNTAX	INTEGER
			MAX-ACCESS	read-only
			STATUS	current
			::= { hmWanMbus31 95 }

hmWanMbus31VIF2D		OBJECT-TYPE
			SYNTAX	INTEGER
			MAX-ACCESS	read-only
			STATUS	current
			::= { hmWanMbus31 96 }

hmWanMbus31Value2D		OBJECT-TYPE
			SYNTAX	INTEGER
			MAX-ACCESS	read-only
			STATUS	current
			::= { hmWanMbus31 97 }

hmWanMbus31VIF2E		OBJECT-TYPE
			SYNTAX	INTEGER
			MAX-ACCESS	read-only
			STATUS	current
			::= { hmWanMbus31 98 }

hmWanMbus31Value2E		OBJECT-TYPE
			SYNTAX	INTEGER
			MAX-ACCESS	read-only
			STATUS	current
			::= { hmWanMbus31 99 }

hmWanMbus31VIF2F		OBJECT-TYPE
			SYNTAX	INTEGER
			MAX-ACCESS	read-only
			STATUS	current
			::= { hmWanMbus31 100 }

hmWanMbus31Value2F		OBJECT-TYPE
			SYNTAX	INTEGER
			MAX-ACCESS	read-only
			STATUS	current
			::= { hmWanMbus31 101 }

hmWanMbus32			OBJECT IDENTIFIER ::= { hmWanMbus 50 }

hmWanMbus32IdNumber		OBJECT-TYPE
			SYNTAX	Gauge32
			MAX-ACCESS	read-only
			STATUS	current
			::= { hmWanMbus32 1 }

hmWanMbus32Manufacturer	OBJECT-TYPE
			SYNTAX	Gauge32
			MAX-ACCESS	read-only
			STATUS	current
			::= { hmWanMbus32 2 }

hmWanMbus32Version		OBJECT-TYPE
			SYNTAX	Gauge32
			MAX-ACCESS	read-only
			STATUS	current
			::= { hmWanMbus32 3 }

hmWanMbus32Medium		OBJECT-TYPE
			SYNTAX	Gauge32
			MAX-ACCESS	read-only
			STATUS	current
			::= { hmWanMbus32 4 }

hmWanMbus32Status		OBJECT-TYPE
			SYNTAX	Gauge32
			MAX-ACCESS	read-only
			STATUS	current
			::= { hmWanMbus32 5 }

hmWanMbus32VIF00		OBJECT-TYPE
			SYNTAX	INTEGER
			MAX-ACCESS	read-only
			STATUS	current
			::= { hmWanMbus32 6 }

hmWanMbus32Value00		OBJECT-TYPE
			SYNTAX	INTEGER
			MAX-ACCESS	read-only
			STATUS	current
			::= { hmWanMbus32 7 }

hmWanMbus32VIF01		OBJECT-TYPE
			SYNTAX	INTEGER
			MAX-ACCESS	read-only
			STATUS	current
			::= { hmWanMbus32 8 }

hmWanMbus32Value01		OBJECT-TYPE
			SYNTAX	INTEGER
			MAX-ACCESS	read-only
			STATUS	current
			::= { hmWanMbus32 9 }

hmWanMbus32VIF02		OBJECT-TYPE
			SYNTAX	INTEGER
			MAX-ACCESS	read-only
			STATUS	current
			::= { hmWanMbus32 10 }

hmWanMbus32Value02		OBJECT-TYPE
			SYNTAX	INTEGER
			MAX-ACCESS	read-only
			STATUS	current
			::= { hmWanMbus32 11 }

hmWanMbus32VIF03		OBJECT-TYPE
			SYNTAX	INTEGER
			MAX-ACCESS	read-only
			STATUS	current
			::= { hmWanMbus32 12 }

hmWanMbus32Value03		OBJECT-TYPE
			SYNTAX	INTEGER
			MAX-ACCESS	read-only
			STATUS	current
			::= { hmWanMbus32 13 }

hmWanMbus32VIF04		OBJECT-TYPE
			SYNTAX	INTEGER
			MAX-ACCESS	read-only
			STATUS	current
			::= { hmWanMbus32 14 }

hmWanMbus32Value04		OBJECT-TYPE
			SYNTAX	INTEGER
			MAX-ACCESS	read-only
			STATUS	current
			::= { hmWanMbus32 15 }

hmWanMbus32VIF05		OBJECT-TYPE
			SYNTAX	INTEGER
			MAX-ACCESS	read-only
			STATUS	current
			::= { hmWanMbus32 16 }

hmWanMbus32Value05		OBJECT-TYPE
			SYNTAX	INTEGER
			MAX-ACCESS	read-only
			STATUS	current
			::= { hmWanMbus32 17 }

hmWanMbus32VIF06		OBJECT-TYPE
			SYNTAX	INTEGER
			MAX-ACCESS	read-only
			STATUS	current
			::= { hmWanMbus32 18 }

hmWanMbus32Value06		OBJECT-TYPE
			SYNTAX	INTEGER
			MAX-ACCESS	read-only
			STATUS	current
			::= { hmWanMbus32 19 }

hmWanMbus32VIF07		OBJECT-TYPE
			SYNTAX	INTEGER
			MAX-ACCESS	read-only
			STATUS	current
			::= { hmWanMbus32 20 }

hmWanMbus32Value07		OBJECT-TYPE
			SYNTAX	INTEGER
			MAX-ACCESS	read-only
			STATUS	current
			::= { hmWanMbus32 21 }

hmWanMbus32VIF08		OBJECT-TYPE
			SYNTAX	INTEGER
			MAX-ACCESS	read-only
			STATUS	current
			::= { hmWanMbus32 22 }

hmWanMbus32Value08		OBJECT-TYPE
			SYNTAX	INTEGER
			MAX-ACCESS	read-only
			STATUS	current
			::= { hmWanMbus32 23 }

hmWanMbus32VIF09		OBJECT-TYPE
			SYNTAX	INTEGER
			MAX-ACCESS	read-only
			STATUS	current
			::= { hmWanMbus32 24 }

hmWanMbus32Value09		OBJECT-TYPE
			SYNTAX	INTEGER
			MAX-ACCESS	read-only
			STATUS	current
			::= { hmWanMbus32 25 }

hmWanMbus32VIF0A		OBJECT-TYPE
			SYNTAX	INTEGER
			MAX-ACCESS	read-only
			STATUS	current
			::= { hmWanMbus32 26 }

hmWanMbus32Value0A		OBJECT-TYPE
			SYNTAX	INTEGER
			MAX-ACCESS	read-only
			STATUS	current
			::= { hmWanMbus32 27 }

hmWanMbus32VIF0B		OBJECT-TYPE
			SYNTAX	INTEGER
			MAX-ACCESS	read-only
			STATUS	current
			::= { hmWanMbus32 28 }

hmWanMbus32Value0B		OBJECT-TYPE
			SYNTAX	INTEGER
			MAX-ACCESS	read-only
			STATUS	current
			::= { hmWanMbus32 29 }

hmWanMbus32VIF0C		OBJECT-TYPE
			SYNTAX	INTEGER
			MAX-ACCESS	read-only
			STATUS	current
			::= { hmWanMbus32 30 }

hmWanMbus32Value0C		OBJECT-TYPE
			SYNTAX	INTEGER
			MAX-ACCESS	read-only
			STATUS	current
			::= { hmWanMbus32 31 }

hmWanMbus32VIF0D		OBJECT-TYPE
			SYNTAX	INTEGER
			MAX-ACCESS	read-only
			STATUS	current
			::= { hmWanMbus32 32 }

hmWanMbus32Value0D		OBJECT-TYPE
			SYNTAX	INTEGER
			MAX-ACCESS	read-only
			STATUS	current
			::= { hmWanMbus32 33 }

hmWanMbus32VIF0E		OBJECT-TYPE
			SYNTAX	INTEGER
			MAX-ACCESS	read-only
			STATUS	current
			::= { hmWanMbus32 34 }

hmWanMbus32Value0E		OBJECT-TYPE
			SYNTAX	INTEGER
			MAX-ACCESS	read-only
			STATUS	current
			::= { hmWanMbus32 35 }

hmWanMbus32VIF0F		OBJECT-TYPE
			SYNTAX	INTEGER
			MAX-ACCESS	read-only
			STATUS	current
			::= { hmWanMbus32 36 }

hmWanMbus32Value0F		OBJECT-TYPE
			SYNTAX	INTEGER
			MAX-ACCESS	read-only
			STATUS	current
			::= { hmWanMbus32 37 }

hmWanMbus32VIF10		OBJECT-TYPE
			SYNTAX	INTEGER
			MAX-ACCESS	read-only
			STATUS	current
			::= { hmWanMbus32 38 }

hmWanMbus32Value10		OBJECT-TYPE
			SYNTAX	INTEGER
			MAX-ACCESS	read-only
			STATUS	current
			::= { hmWanMbus32 39 }

hmWanMbus32VIF11		OBJECT-TYPE
			SYNTAX	INTEGER
			MAX-ACCESS	read-only
			STATUS	current
			::= { hmWanMbus32 40 }

hmWanMbus32Value11		OBJECT-TYPE
			SYNTAX	INTEGER
			MAX-ACCESS	read-only
			STATUS	current
			::= { hmWanMbus32 41 }

hmWanMbus32VIF12		OBJECT-TYPE
			SYNTAX	INTEGER
			MAX-ACCESS	read-only
			STATUS	current
			::= { hmWanMbus32 42 }

hmWanMbus32Value12		OBJECT-TYPE
			SYNTAX	INTEGER
			MAX-ACCESS	read-only
			STATUS	current
			::= { hmWanMbus32 43 }

hmWanMbus32VIF13		OBJECT-TYPE
			SYNTAX	INTEGER
			MAX-ACCESS	read-only
			STATUS	current
			::= { hmWanMbus32 44 }

hmWanMbus32Value13		OBJECT-TYPE
			SYNTAX	INTEGER
			MAX-ACCESS	read-only
			STATUS	current
			::= { hmWanMbus32 45 }

hmWanMbus32VIF14		OBJECT-TYPE
			SYNTAX	INTEGER
			MAX-ACCESS	read-only
			STATUS	current
			::= { hmWanMbus32 46 }

hmWanMbus32Value14		OBJECT-TYPE
			SYNTAX	INTEGER
			MAX-ACCESS	read-only
			STATUS	current
			::= { hmWanMbus32 47 }

hmWanMbus32VIF15		OBJECT-TYPE
			SYNTAX	INTEGER
			MAX-ACCESS	read-only
			STATUS	current
			::= { hmWanMbus32 48 }

hmWanMbus32Value15		OBJECT-TYPE
			SYNTAX	INTEGER
			MAX-ACCESS	read-only
			STATUS	current
			::= { hmWanMbus32 49 }

hmWanMbus32VIF16		OBJECT-TYPE
			SYNTAX	INTEGER
			MAX-ACCESS	read-only
			STATUS	current
			::= { hmWanMbus32 50 }

hmWanMbus32Value16		OBJECT-TYPE
			SYNTAX	INTEGER
			MAX-ACCESS	read-only
			STATUS	current
			::= { hmWanMbus32 51 }

hmWanMbus32VIF17		OBJECT-TYPE
			SYNTAX	INTEGER
			MAX-ACCESS	read-only
			STATUS	current
			::= { hmWanMbus32 52 }

hmWanMbus32Value17		OBJECT-TYPE
			SYNTAX	INTEGER
			MAX-ACCESS	read-only
			STATUS	current
			::= { hmWanMbus32 53 }

hmWanMbus32VIF18		OBJECT-TYPE
			SYNTAX	INTEGER
			MAX-ACCESS	read-only
			STATUS	current
			::= { hmWanMbus32 54 }

hmWanMbus32Value18		OBJECT-TYPE
			SYNTAX	INTEGER
			MAX-ACCESS	read-only
			STATUS	current
			::= { hmWanMbus32 55 }

hmWanMbus32VIF19		OBJECT-TYPE
			SYNTAX	INTEGER
			MAX-ACCESS	read-only
			STATUS	current
			::= { hmWanMbus32 56 }

hmWanMbus32Value19		OBJECT-TYPE
			SYNTAX	INTEGER
			MAX-ACCESS	read-only
			STATUS	current
			::= { hmWanMbus32 57 }

hmWanMbus32VIF1A		OBJECT-TYPE
			SYNTAX	INTEGER
			MAX-ACCESS	read-only
			STATUS	current
			::= { hmWanMbus32 58 }

hmWanMbus32Value1A		OBJECT-TYPE
			SYNTAX	INTEGER
			MAX-ACCESS	read-only
			STATUS	current
			::= { hmWanMbus32 59 }

hmWanMbus32VIF1B		OBJECT-TYPE
			SYNTAX	INTEGER
			MAX-ACCESS	read-only
			STATUS	current
			::= { hmWanMbus32 60 }

hmWanMbus32Value1B		OBJECT-TYPE
			SYNTAX	INTEGER
			MAX-ACCESS	read-only
			STATUS	current
			::= { hmWanMbus32 61 }

hmWanMbus32VIF1C		OBJECT-TYPE
			SYNTAX	INTEGER
			MAX-ACCESS	read-only
			STATUS	current
			::= { hmWanMbus32 62 }

hmWanMbus32Value1C		OBJECT-TYPE
			SYNTAX	INTEGER
			MAX-ACCESS	read-only
			STATUS	current
			::= { hmWanMbus32 63 }

hmWanMbus32VIF1D		OBJECT-TYPE
			SYNTAX	INTEGER
			MAX-ACCESS	read-only
			STATUS	current
			::= { hmWanMbus32 64 }

hmWanMbus32Value1D		OBJECT-TYPE
			SYNTAX	INTEGER
			MAX-ACCESS	read-only
			STATUS	current
			::= { hmWanMbus32 65 }

hmWanMbus32VIF1E		OBJECT-TYPE
			SYNTAX	INTEGER
			MAX-ACCESS	read-only
			STATUS	current
			::= { hmWanMbus32 66 }

hmWanMbus32Value1E		OBJECT-TYPE
			SYNTAX	INTEGER
			MAX-ACCESS	read-only
			STATUS	current
			::= { hmWanMbus32 67 }

hmWanMbus32VIF1F		OBJECT-TYPE
			SYNTAX	INTEGER
			MAX-ACCESS	read-only
			STATUS	current
			::= { hmWanMbus32 68 }

hmWanMbus32Value1F		OBJECT-TYPE
			SYNTAX	INTEGER
			MAX-ACCESS	read-only
			STATUS	current
			::= { hmWanMbus32 69 }

hmWanMbus32VIF20		OBJECT-TYPE
			SYNTAX	INTEGER
			MAX-ACCESS	read-only
			STATUS	current
			::= { hmWanMbus32 70 }

hmWanMbus32Value20		OBJECT-TYPE
			SYNTAX	INTEGER
			MAX-ACCESS	read-only
			STATUS	current
			::= { hmWanMbus32 71 }

hmWanMbus32VIF21		OBJECT-TYPE
			SYNTAX	INTEGER
			MAX-ACCESS	read-only
			STATUS	current
			::= { hmWanMbus32 72 }

hmWanMbus32Value21		OBJECT-TYPE
			SYNTAX	INTEGER
			MAX-ACCESS	read-only
			STATUS	current
			::= { hmWanMbus32 73 }

hmWanMbus32VIF22		OBJECT-TYPE
			SYNTAX	INTEGER
			MAX-ACCESS	read-only
			STATUS	current
			::= { hmWanMbus32 74 }

hmWanMbus32Value22		OBJECT-TYPE
			SYNTAX	INTEGER
			MAX-ACCESS	read-only
			STATUS	current
			::= { hmWanMbus32 75 }

hmWanMbus32VIF23		OBJECT-TYPE
			SYNTAX	INTEGER
			MAX-ACCESS	read-only
			STATUS	current
			::= { hmWanMbus32 76 }

hmWanMbus32Value23		OBJECT-TYPE
			SYNTAX	INTEGER
			MAX-ACCESS	read-only
			STATUS	current
			::= { hmWanMbus32 77 }

hmWanMbus32VIF24		OBJECT-TYPE
			SYNTAX	INTEGER
			MAX-ACCESS	read-only
			STATUS	current
			::= { hmWanMbus32 78 }

hmWanMbus32Value24		OBJECT-TYPE
			SYNTAX	INTEGER
			MAX-ACCESS	read-only
			STATUS	current
			::= { hmWanMbus32 79 }

hmWanMbus32VIF25		OBJECT-TYPE
			SYNTAX	INTEGER
			MAX-ACCESS	read-only
			STATUS	current
			::= { hmWanMbus32 80 }

hmWanMbus32Value25		OBJECT-TYPE
			SYNTAX	INTEGER
			MAX-ACCESS	read-only
			STATUS	current
			::= { hmWanMbus32 81 }

hmWanMbus32VIF26		OBJECT-TYPE
			SYNTAX	INTEGER
			MAX-ACCESS	read-only
			STATUS	current
			::= { hmWanMbus32 82 }

hmWanMbus32Value26		OBJECT-TYPE
			SYNTAX	INTEGER
			MAX-ACCESS	read-only
			STATUS	current
			::= { hmWanMbus32 83 }

hmWanMbus32VIF27		OBJECT-TYPE
			SYNTAX	INTEGER
			MAX-ACCESS	read-only
			STATUS	current
			::= { hmWanMbus32 84 }

hmWanMbus32Value27		OBJECT-TYPE
			SYNTAX	INTEGER
			MAX-ACCESS	read-only
			STATUS	current
			::= { hmWanMbus32 85 }

hmWanMbus32VIF28		OBJECT-TYPE
			SYNTAX	INTEGER
			MAX-ACCESS	read-only
			STATUS	current
			::= { hmWanMbus32 86 }

hmWanMbus32Value28		OBJECT-TYPE
			SYNTAX	INTEGER
			MAX-ACCESS	read-only
			STATUS	current
			::= { hmWanMbus32 87 }

hmWanMbus32VIF29		OBJECT-TYPE
			SYNTAX	INTEGER
			MAX-ACCESS	read-only
			STATUS	current
			::= { hmWanMbus32 88 }

hmWanMbus32Value29		OBJECT-TYPE
			SYNTAX	INTEGER
			MAX-ACCESS	read-only
			STATUS	current
			::= { hmWanMbus32 89 }

hmWanMbus32VIF2A		OBJECT-TYPE
			SYNTAX	INTEGER
			MAX-ACCESS	read-only
			STATUS	current
			::= { hmWanMbus32 90 }

hmWanMbus32Value2A		OBJECT-TYPE
			SYNTAX	INTEGER
			MAX-ACCESS	read-only
			STATUS	current
			::= { hmWanMbus32 91 }

hmWanMbus32VIF2B		OBJECT-TYPE
			SYNTAX	INTEGER
			MAX-ACCESS	read-only
			STATUS	current
			::= { hmWanMbus32 92 }

hmWanMbus32Value2B		OBJECT-TYPE
			SYNTAX	INTEGER
			MAX-ACCESS	read-only
			STATUS	current
			::= { hmWanMbus32 93 }

hmWanMbus32VIF2C		OBJECT-TYPE
			SYNTAX	INTEGER
			MAX-ACCESS	read-only
			STATUS	current
			::= { hmWanMbus32 94 }

hmWanMbus32Value2C		OBJECT-TYPE
			SYNTAX	INTEGER
			MAX-ACCESS	read-only
			STATUS	current
			::= { hmWanMbus32 95 }

hmWanMbus32VIF2D		OBJECT-TYPE
			SYNTAX	INTEGER
			MAX-ACCESS	read-only
			STATUS	current
			::= { hmWanMbus32 96 }

hmWanMbus32Value2D		OBJECT-TYPE
			SYNTAX	INTEGER
			MAX-ACCESS	read-only
			STATUS	current
			::= { hmWanMbus32 97 }

hmWanMbus32VIF2E		OBJECT-TYPE
			SYNTAX	INTEGER
			MAX-ACCESS	read-only
			STATUS	current
			::= { hmWanMbus32 98 }

hmWanMbus32Value2E		OBJECT-TYPE
			SYNTAX	INTEGER
			MAX-ACCESS	read-only
			STATUS	current
			::= { hmWanMbus32 99 }

hmWanMbus32VIF2F		OBJECT-TYPE
			SYNTAX	INTEGER
			MAX-ACCESS	read-only
			STATUS	current
			::= { hmWanMbus32 100 }

hmWanMbus32Value2F		OBJECT-TYPE
			SYNTAX	INTEGER
			MAX-ACCESS	read-only
			STATUS	current
			::= { hmWanMbus32 101 }

hmWanMbus33			OBJECT IDENTIFIER ::= { hmWanMbus 51 }

hmWanMbus33IdNumber		OBJECT-TYPE
			SYNTAX	Gauge32
			MAX-ACCESS	read-only
			STATUS	current
			::= { hmWanMbus33 1 }

hmWanMbus33Manufacturer	OBJECT-TYPE
			SYNTAX	Gauge32
			MAX-ACCESS	read-only
			STATUS	current
			::= { hmWanMbus33 2 }

hmWanMbus33Version		OBJECT-TYPE
			SYNTAX	Gauge32
			MAX-ACCESS	read-only
			STATUS	current
			::= { hmWanMbus33 3 }

hmWanMbus33Medium		OBJECT-TYPE
			SYNTAX	Gauge32
			MAX-ACCESS	read-only
			STATUS	current
			::= { hmWanMbus33 4 }

hmWanMbus33Status		OBJECT-TYPE
			SYNTAX	Gauge32
			MAX-ACCESS	read-only
			STATUS	current
			::= { hmWanMbus33 5 }

hmWanMbus33VIF00		OBJECT-TYPE
			SYNTAX	INTEGER
			MAX-ACCESS	read-only
			STATUS	current
			::= { hmWanMbus33 6 }

hmWanMbus33Value00		OBJECT-TYPE
			SYNTAX	INTEGER
			MAX-ACCESS	read-only
			STATUS	current
			::= { hmWanMbus33 7 }

hmWanMbus33VIF01		OBJECT-TYPE
			SYNTAX	INTEGER
			MAX-ACCESS	read-only
			STATUS	current
			::= { hmWanMbus33 8 }

hmWanMbus33Value01		OBJECT-TYPE
			SYNTAX	INTEGER
			MAX-ACCESS	read-only
			STATUS	current
			::= { hmWanMbus33 9 }

hmWanMbus33VIF02		OBJECT-TYPE
			SYNTAX	INTEGER
			MAX-ACCESS	read-only
			STATUS	current
			::= { hmWanMbus33 10 }

hmWanMbus33Value02		OBJECT-TYPE
			SYNTAX	INTEGER
			MAX-ACCESS	read-only
			STATUS	current
			::= { hmWanMbus33 11 }

hmWanMbus33VIF03		OBJECT-TYPE
			SYNTAX	INTEGER
			MAX-ACCESS	read-only
			STATUS	current
			::= { hmWanMbus33 12 }

hmWanMbus33Value03		OBJECT-TYPE
			SYNTAX	INTEGER
			MAX-ACCESS	read-only
			STATUS	current
			::= { hmWanMbus33 13 }

hmWanMbus33VIF04		OBJECT-TYPE
			SYNTAX	INTEGER
			MAX-ACCESS	read-only
			STATUS	current
			::= { hmWanMbus33 14 }

hmWanMbus33Value04		OBJECT-TYPE
			SYNTAX	INTEGER
			MAX-ACCESS	read-only
			STATUS	current
			::= { hmWanMbus33 15 }

hmWanMbus33VIF05		OBJECT-TYPE
			SYNTAX	INTEGER
			MAX-ACCESS	read-only
			STATUS	current
			::= { hmWanMbus33 16 }

hmWanMbus33Value05		OBJECT-TYPE
			SYNTAX	INTEGER
			MAX-ACCESS	read-only
			STATUS	current
			::= { hmWanMbus33 17 }

hmWanMbus33VIF06		OBJECT-TYPE
			SYNTAX	INTEGER
			MAX-ACCESS	read-only
			STATUS	current
			::= { hmWanMbus33 18 }

hmWanMbus33Value06		OBJECT-TYPE
			SYNTAX	INTEGER
			MAX-ACCESS	read-only
			STATUS	current
			::= { hmWanMbus33 19 }

hmWanMbus33VIF07		OBJECT-TYPE
			SYNTAX	INTEGER
			MAX-ACCESS	read-only
			STATUS	current
			::= { hmWanMbus33 20 }

hmWanMbus33Value07		OBJECT-TYPE
			SYNTAX	INTEGER
			MAX-ACCESS	read-only
			STATUS	current
			::= { hmWanMbus33 21 }

hmWanMbus33VIF08		OBJECT-TYPE
			SYNTAX	INTEGER
			MAX-ACCESS	read-only
			STATUS	current
			::= { hmWanMbus33 22 }

hmWanMbus33Value08		OBJECT-TYPE
			SYNTAX	INTEGER
			MAX-ACCESS	read-only
			STATUS	current
			::= { hmWanMbus33 23 }

hmWanMbus33VIF09		OBJECT-TYPE
			SYNTAX	INTEGER
			MAX-ACCESS	read-only
			STATUS	current
			::= { hmWanMbus33 24 }

hmWanMbus33Value09		OBJECT-TYPE
			SYNTAX	INTEGER
			MAX-ACCESS	read-only
			STATUS	current
			::= { hmWanMbus33 25 }

hmWanMbus33VIF0A		OBJECT-TYPE
			SYNTAX	INTEGER
			MAX-ACCESS	read-only
			STATUS	current
			::= { hmWanMbus33 26 }

hmWanMbus33Value0A		OBJECT-TYPE
			SYNTAX	INTEGER
			MAX-ACCESS	read-only
			STATUS	current
			::= { hmWanMbus33 27 }

hmWanMbus33VIF0B		OBJECT-TYPE
			SYNTAX	INTEGER
			MAX-ACCESS	read-only
			STATUS	current
			::= { hmWanMbus33 28 }

hmWanMbus33Value0B		OBJECT-TYPE
			SYNTAX	INTEGER
			MAX-ACCESS	read-only
			STATUS	current
			::= { hmWanMbus33 29 }

hmWanMbus33VIF0C		OBJECT-TYPE
			SYNTAX	INTEGER
			MAX-ACCESS	read-only
			STATUS	current
			::= { hmWanMbus33 30 }

hmWanMbus33Value0C		OBJECT-TYPE
			SYNTAX	INTEGER
			MAX-ACCESS	read-only
			STATUS	current
			::= { hmWanMbus33 31 }

hmWanMbus33VIF0D		OBJECT-TYPE
			SYNTAX	INTEGER
			MAX-ACCESS	read-only
			STATUS	current
			::= { hmWanMbus33 32 }

hmWanMbus33Value0D		OBJECT-TYPE
			SYNTAX	INTEGER
			MAX-ACCESS	read-only
			STATUS	current
			::= { hmWanMbus33 33 }

hmWanMbus33VIF0E		OBJECT-TYPE
			SYNTAX	INTEGER
			MAX-ACCESS	read-only
			STATUS	current
			::= { hmWanMbus33 34 }

hmWanMbus33Value0E		OBJECT-TYPE
			SYNTAX	INTEGER
			MAX-ACCESS	read-only
			STATUS	current
			::= { hmWanMbus33 35 }

hmWanMbus33VIF0F		OBJECT-TYPE
			SYNTAX	INTEGER
			MAX-ACCESS	read-only
			STATUS	current
			::= { hmWanMbus33 36 }

hmWanMbus33Value0F		OBJECT-TYPE
			SYNTAX	INTEGER
			MAX-ACCESS	read-only
			STATUS	current
			::= { hmWanMbus33 37 }

hmWanMbus33VIF10		OBJECT-TYPE
			SYNTAX	INTEGER
			MAX-ACCESS	read-only
			STATUS	current
			::= { hmWanMbus33 38 }

hmWanMbus33Value10		OBJECT-TYPE
			SYNTAX	INTEGER
			MAX-ACCESS	read-only
			STATUS	current
			::= { hmWanMbus33 39 }

hmWanMbus33VIF11		OBJECT-TYPE
			SYNTAX	INTEGER
			MAX-ACCESS	read-only
			STATUS	current
			::= { hmWanMbus33 40 }

hmWanMbus33Value11		OBJECT-TYPE
			SYNTAX	INTEGER
			MAX-ACCESS	read-only
			STATUS	current
			::= { hmWanMbus33 41 }

hmWanMbus33VIF12		OBJECT-TYPE
			SYNTAX	INTEGER
			MAX-ACCESS	read-only
			STATUS	current
			::= { hmWanMbus33 42 }

hmWanMbus33Value12		OBJECT-TYPE
			SYNTAX	INTEGER
			MAX-ACCESS	read-only
			STATUS	current
			::= { hmWanMbus33 43 }

hmWanMbus33VIF13		OBJECT-TYPE
			SYNTAX	INTEGER
			MAX-ACCESS	read-only
			STATUS	current
			::= { hmWanMbus33 44 }

hmWanMbus33Value13		OBJECT-TYPE
			SYNTAX	INTEGER
			MAX-ACCESS	read-only
			STATUS	current
			::= { hmWanMbus33 45 }

hmWanMbus33VIF14		OBJECT-TYPE
			SYNTAX	INTEGER
			MAX-ACCESS	read-only
			STATUS	current
			::= { hmWanMbus33 46 }

hmWanMbus33Value14		OBJECT-TYPE
			SYNTAX	INTEGER
			MAX-ACCESS	read-only
			STATUS	current
			::= { hmWanMbus33 47 }

hmWanMbus33VIF15		OBJECT-TYPE
			SYNTAX	INTEGER
			MAX-ACCESS	read-only
			STATUS	current
			::= { hmWanMbus33 48 }

hmWanMbus33Value15		OBJECT-TYPE
			SYNTAX	INTEGER
			MAX-ACCESS	read-only
			STATUS	current
			::= { hmWanMbus33 49 }

hmWanMbus33VIF16		OBJECT-TYPE
			SYNTAX	INTEGER
			MAX-ACCESS	read-only
			STATUS	current
			::= { hmWanMbus33 50 }

hmWanMbus33Value16		OBJECT-TYPE
			SYNTAX	INTEGER
			MAX-ACCESS	read-only
			STATUS	current
			::= { hmWanMbus33 51 }

hmWanMbus33VIF17		OBJECT-TYPE
			SYNTAX	INTEGER
			MAX-ACCESS	read-only
			STATUS	current
			::= { hmWanMbus33 52 }

hmWanMbus33Value17		OBJECT-TYPE
			SYNTAX	INTEGER
			MAX-ACCESS	read-only
			STATUS	current
			::= { hmWanMbus33 53 }

hmWanMbus33VIF18		OBJECT-TYPE
			SYNTAX	INTEGER
			MAX-ACCESS	read-only
			STATUS	current
			::= { hmWanMbus33 54 }

hmWanMbus33Value18		OBJECT-TYPE
			SYNTAX	INTEGER
			MAX-ACCESS	read-only
			STATUS	current
			::= { hmWanMbus33 55 }

hmWanMbus33VIF19		OBJECT-TYPE
			SYNTAX	INTEGER
			MAX-ACCESS	read-only
			STATUS	current
			::= { hmWanMbus33 56 }

hmWanMbus33Value19		OBJECT-TYPE
			SYNTAX	INTEGER
			MAX-ACCESS	read-only
			STATUS	current
			::= { hmWanMbus33 57 }

hmWanMbus33VIF1A		OBJECT-TYPE
			SYNTAX	INTEGER
			MAX-ACCESS	read-only
			STATUS	current
			::= { hmWanMbus33 58 }

hmWanMbus33Value1A		OBJECT-TYPE
			SYNTAX	INTEGER
			MAX-ACCESS	read-only
			STATUS	current
			::= { hmWanMbus33 59 }

hmWanMbus33VIF1B		OBJECT-TYPE
			SYNTAX	INTEGER
			MAX-ACCESS	read-only
			STATUS	current
			::= { hmWanMbus33 60 }

hmWanMbus33Value1B		OBJECT-TYPE
			SYNTAX	INTEGER
			MAX-ACCESS	read-only
			STATUS	current
			::= { hmWanMbus33 61 }

hmWanMbus33VIF1C		OBJECT-TYPE
			SYNTAX	INTEGER
			MAX-ACCESS	read-only
			STATUS	current
			::= { hmWanMbus33 62 }

hmWanMbus33Value1C		OBJECT-TYPE
			SYNTAX	INTEGER
			MAX-ACCESS	read-only
			STATUS	current
			::= { hmWanMbus33 63 }

hmWanMbus33VIF1D		OBJECT-TYPE
			SYNTAX	INTEGER
			MAX-ACCESS	read-only
			STATUS	current
			::= { hmWanMbus33 64 }

hmWanMbus33Value1D		OBJECT-TYPE
			SYNTAX	INTEGER
			MAX-ACCESS	read-only
			STATUS	current
			::= { hmWanMbus33 65 }

hmWanMbus33VIF1E		OBJECT-TYPE
			SYNTAX	INTEGER
			MAX-ACCESS	read-only
			STATUS	current
			::= { hmWanMbus33 66 }

hmWanMbus33Value1E		OBJECT-TYPE
			SYNTAX	INTEGER
			MAX-ACCESS	read-only
			STATUS	current
			::= { hmWanMbus33 67 }

hmWanMbus33VIF1F		OBJECT-TYPE
			SYNTAX	INTEGER
			MAX-ACCESS	read-only
			STATUS	current
			::= { hmWanMbus33 68 }

hmWanMbus33Value1F		OBJECT-TYPE
			SYNTAX	INTEGER
			MAX-ACCESS	read-only
			STATUS	current
			::= { hmWanMbus33 69 }

hmWanMbus33VIF20		OBJECT-TYPE
			SYNTAX	INTEGER
			MAX-ACCESS	read-only
			STATUS	current
			::= { hmWanMbus33 70 }

hmWanMbus33Value20		OBJECT-TYPE
			SYNTAX	INTEGER
			MAX-ACCESS	read-only
			STATUS	current
			::= { hmWanMbus33 71 }

hmWanMbus33VIF21		OBJECT-TYPE
			SYNTAX	INTEGER
			MAX-ACCESS	read-only
			STATUS	current
			::= { hmWanMbus33 72 }

hmWanMbus33Value21		OBJECT-TYPE
			SYNTAX	INTEGER
			MAX-ACCESS	read-only
			STATUS	current
			::= { hmWanMbus33 73 }

hmWanMbus33VIF22		OBJECT-TYPE
			SYNTAX	INTEGER
			MAX-ACCESS	read-only
			STATUS	current
			::= { hmWanMbus33 74 }

hmWanMbus33Value22		OBJECT-TYPE
			SYNTAX	INTEGER
			MAX-ACCESS	read-only
			STATUS	current
			::= { hmWanMbus33 75 }

hmWanMbus33VIF23		OBJECT-TYPE
			SYNTAX	INTEGER
			MAX-ACCESS	read-only
			STATUS	current
			::= { hmWanMbus33 76 }

hmWanMbus33Value23		OBJECT-TYPE
			SYNTAX	INTEGER
			MAX-ACCESS	read-only
			STATUS	current
			::= { hmWanMbus33 77 }

hmWanMbus33VIF24		OBJECT-TYPE
			SYNTAX	INTEGER
			MAX-ACCESS	read-only
			STATUS	current
			::= { hmWanMbus33 78 }

hmWanMbus33Value24		OBJECT-TYPE
			SYNTAX	INTEGER
			MAX-ACCESS	read-only
			STATUS	current
			::= { hmWanMbus33 79 }

hmWanMbus33VIF25		OBJECT-TYPE
			SYNTAX	INTEGER
			MAX-ACCESS	read-only
			STATUS	current
			::= { hmWanMbus33 80 }

hmWanMbus33Value25		OBJECT-TYPE
			SYNTAX	INTEGER
			MAX-ACCESS	read-only
			STATUS	current
			::= { hmWanMbus33 81 }

hmWanMbus33VIF26		OBJECT-TYPE
			SYNTAX	INTEGER
			MAX-ACCESS	read-only
			STATUS	current
			::= { hmWanMbus33 82 }

hmWanMbus33Value26		OBJECT-TYPE
			SYNTAX	INTEGER
			MAX-ACCESS	read-only
			STATUS	current
			::= { hmWanMbus33 83 }

hmWanMbus33VIF27		OBJECT-TYPE
			SYNTAX	INTEGER
			MAX-ACCESS	read-only
			STATUS	current
			::= { hmWanMbus33 84 }

hmWanMbus33Value27		OBJECT-TYPE
			SYNTAX	INTEGER
			MAX-ACCESS	read-only
			STATUS	current
			::= { hmWanMbus33 85 }

hmWanMbus33VIF28		OBJECT-TYPE
			SYNTAX	INTEGER
			MAX-ACCESS	read-only
			STATUS	current
			::= { hmWanMbus33 86 }

hmWanMbus33Value28		OBJECT-TYPE
			SYNTAX	INTEGER
			MAX-ACCESS	read-only
			STATUS	current
			::= { hmWanMbus33 87 }

hmWanMbus33VIF29		OBJECT-TYPE
			SYNTAX	INTEGER
			MAX-ACCESS	read-only
			STATUS	current
			::= { hmWanMbus33 88 }

hmWanMbus33Value29		OBJECT-TYPE
			SYNTAX	INTEGER
			MAX-ACCESS	read-only
			STATUS	current
			::= { hmWanMbus33 89 }

hmWanMbus33VIF2A		OBJECT-TYPE
			SYNTAX	INTEGER
			MAX-ACCESS	read-only
			STATUS	current
			::= { hmWanMbus33 90 }

hmWanMbus33Value2A		OBJECT-TYPE
			SYNTAX	INTEGER
			MAX-ACCESS	read-only
			STATUS	current
			::= { hmWanMbus33 91 }

hmWanMbus33VIF2B		OBJECT-TYPE
			SYNTAX	INTEGER
			MAX-ACCESS	read-only
			STATUS	current
			::= { hmWanMbus33 92 }

hmWanMbus33Value2B		OBJECT-TYPE
			SYNTAX	INTEGER
			MAX-ACCESS	read-only
			STATUS	current
			::= { hmWanMbus33 93 }

hmWanMbus33VIF2C		OBJECT-TYPE
			SYNTAX	INTEGER
			MAX-ACCESS	read-only
			STATUS	current
			::= { hmWanMbus33 94 }

hmWanMbus33Value2C		OBJECT-TYPE
			SYNTAX	INTEGER
			MAX-ACCESS	read-only
			STATUS	current
			::= { hmWanMbus33 95 }

hmWanMbus33VIF2D		OBJECT-TYPE
			SYNTAX	INTEGER
			MAX-ACCESS	read-only
			STATUS	current
			::= { hmWanMbus33 96 }

hmWanMbus33Value2D		OBJECT-TYPE
			SYNTAX	INTEGER
			MAX-ACCESS	read-only
			STATUS	current
			::= { hmWanMbus33 97 }

hmWanMbus33VIF2E		OBJECT-TYPE
			SYNTAX	INTEGER
			MAX-ACCESS	read-only
			STATUS	current
			::= { hmWanMbus33 98 }

hmWanMbus33Value2E		OBJECT-TYPE
			SYNTAX	INTEGER
			MAX-ACCESS	read-only
			STATUS	current
			::= { hmWanMbus33 99 }

hmWanMbus33VIF2F		OBJECT-TYPE
			SYNTAX	INTEGER
			MAX-ACCESS	read-only
			STATUS	current
			::= { hmWanMbus33 100 }

hmWanMbus33Value2F		OBJECT-TYPE
			SYNTAX	INTEGER
			MAX-ACCESS	read-only
			STATUS	current
			::= { hmWanMbus33 101 }

hmWanMbus34			OBJECT IDENTIFIER ::= { hmWanMbus 52 }

hmWanMbus34IdNumber		OBJECT-TYPE
			SYNTAX	Gauge32
			MAX-ACCESS	read-only
			STATUS	current
			::= { hmWanMbus34 1 }

hmWanMbus34Manufacturer	OBJECT-TYPE
			SYNTAX	Gauge32
			MAX-ACCESS	read-only
			STATUS	current
			::= { hmWanMbus34 2 }

hmWanMbus34Version		OBJECT-TYPE
			SYNTAX	Gauge32
			MAX-ACCESS	read-only
			STATUS	current
			::= { hmWanMbus34 3 }

hmWanMbus34Medium		OBJECT-TYPE
			SYNTAX	Gauge32
			MAX-ACCESS	read-only
			STATUS	current
			::= { hmWanMbus34 4 }

hmWanMbus34Status		OBJECT-TYPE
			SYNTAX	Gauge32
			MAX-ACCESS	read-only
			STATUS	current
			::= { hmWanMbus34 5 }

hmWanMbus34VIF00		OBJECT-TYPE
			SYNTAX	INTEGER
			MAX-ACCESS	read-only
			STATUS	current
			::= { hmWanMbus34 6 }

hmWanMbus34Value00		OBJECT-TYPE
			SYNTAX	INTEGER
			MAX-ACCESS	read-only
			STATUS	current
			::= { hmWanMbus34 7 }

hmWanMbus34VIF01		OBJECT-TYPE
			SYNTAX	INTEGER
			MAX-ACCESS	read-only
			STATUS	current
			::= { hmWanMbus34 8 }

hmWanMbus34Value01		OBJECT-TYPE
			SYNTAX	INTEGER
			MAX-ACCESS	read-only
			STATUS	current
			::= { hmWanMbus34 9 }

hmWanMbus34VIF02		OBJECT-TYPE
			SYNTAX	INTEGER
			MAX-ACCESS	read-only
			STATUS	current
			::= { hmWanMbus34 10 }

hmWanMbus34Value02		OBJECT-TYPE
			SYNTAX	INTEGER
			MAX-ACCESS	read-only
			STATUS	current
			::= { hmWanMbus34 11 }

hmWanMbus34VIF03		OBJECT-TYPE
			SYNTAX	INTEGER
			MAX-ACCESS	read-only
			STATUS	current
			::= { hmWanMbus34 12 }

hmWanMbus34Value03		OBJECT-TYPE
			SYNTAX	INTEGER
			MAX-ACCESS	read-only
			STATUS	current
			::= { hmWanMbus34 13 }

hmWanMbus34VIF04		OBJECT-TYPE
			SYNTAX	INTEGER
			MAX-ACCESS	read-only
			STATUS	current
			::= { hmWanMbus34 14 }

hmWanMbus34Value04		OBJECT-TYPE
			SYNTAX	INTEGER
			MAX-ACCESS	read-only
			STATUS	current
			::= { hmWanMbus34 15 }

hmWanMbus34VIF05		OBJECT-TYPE
			SYNTAX	INTEGER
			MAX-ACCESS	read-only
			STATUS	current
			::= { hmWanMbus34 16 }

hmWanMbus34Value05		OBJECT-TYPE
			SYNTAX	INTEGER
			MAX-ACCESS	read-only
			STATUS	current
			::= { hmWanMbus34 17 }

hmWanMbus34VIF06		OBJECT-TYPE
			SYNTAX	INTEGER
			MAX-ACCESS	read-only
			STATUS	current
			::= { hmWanMbus34 18 }

hmWanMbus34Value06		OBJECT-TYPE
			SYNTAX	INTEGER
			MAX-ACCESS	read-only
			STATUS	current
			::= { hmWanMbus34 19 }

hmWanMbus34VIF07		OBJECT-TYPE
			SYNTAX	INTEGER
			MAX-ACCESS	read-only
			STATUS	current
			::= { hmWanMbus34 20 }

hmWanMbus34Value07		OBJECT-TYPE
			SYNTAX	INTEGER
			MAX-ACCESS	read-only
			STATUS	current
			::= { hmWanMbus34 21 }

hmWanMbus34VIF08		OBJECT-TYPE
			SYNTAX	INTEGER
			MAX-ACCESS	read-only
			STATUS	current
			::= { hmWanMbus34 22 }

hmWanMbus34Value08		OBJECT-TYPE
			SYNTAX	INTEGER
			MAX-ACCESS	read-only
			STATUS	current
			::= { hmWanMbus34 23 }

hmWanMbus34VIF09		OBJECT-TYPE
			SYNTAX	INTEGER
			MAX-ACCESS	read-only
			STATUS	current
			::= { hmWanMbus34 24 }

hmWanMbus34Value09		OBJECT-TYPE
			SYNTAX	INTEGER
			MAX-ACCESS	read-only
			STATUS	current
			::= { hmWanMbus34 25 }

hmWanMbus34VIF0A		OBJECT-TYPE
			SYNTAX	INTEGER
			MAX-ACCESS	read-only
			STATUS	current
			::= { hmWanMbus34 26 }

hmWanMbus34Value0A		OBJECT-TYPE
			SYNTAX	INTEGER
			MAX-ACCESS	read-only
			STATUS	current
			::= { hmWanMbus34 27 }

hmWanMbus34VIF0B		OBJECT-TYPE
			SYNTAX	INTEGER
			MAX-ACCESS	read-only
			STATUS	current
			::= { hmWanMbus34 28 }

hmWanMbus34Value0B		OBJECT-TYPE
			SYNTAX	INTEGER
			MAX-ACCESS	read-only
			STATUS	current
			::= { hmWanMbus34 29 }

hmWanMbus34VIF0C		OBJECT-TYPE
			SYNTAX	INTEGER
			MAX-ACCESS	read-only
			STATUS	current
			::= { hmWanMbus34 30 }

hmWanMbus34Value0C		OBJECT-TYPE
			SYNTAX	INTEGER
			MAX-ACCESS	read-only
			STATUS	current
			::= { hmWanMbus34 31 }

hmWanMbus34VIF0D		OBJECT-TYPE
			SYNTAX	INTEGER
			MAX-ACCESS	read-only
			STATUS	current
			::= { hmWanMbus34 32 }

hmWanMbus34Value0D		OBJECT-TYPE
			SYNTAX	INTEGER
			MAX-ACCESS	read-only
			STATUS	current
			::= { hmWanMbus34 33 }

hmWanMbus34VIF0E		OBJECT-TYPE
			SYNTAX	INTEGER
			MAX-ACCESS	read-only
			STATUS	current
			::= { hmWanMbus34 34 }

hmWanMbus34Value0E		OBJECT-TYPE
			SYNTAX	INTEGER
			MAX-ACCESS	read-only
			STATUS	current
			::= { hmWanMbus34 35 }

hmWanMbus34VIF0F		OBJECT-TYPE
			SYNTAX	INTEGER
			MAX-ACCESS	read-only
			STATUS	current
			::= { hmWanMbus34 36 }

hmWanMbus34Value0F		OBJECT-TYPE
			SYNTAX	INTEGER
			MAX-ACCESS	read-only
			STATUS	current
			::= { hmWanMbus34 37 }

hmWanMbus34VIF10		OBJECT-TYPE
			SYNTAX	INTEGER
			MAX-ACCESS	read-only
			STATUS	current
			::= { hmWanMbus34 38 }

hmWanMbus34Value10		OBJECT-TYPE
			SYNTAX	INTEGER
			MAX-ACCESS	read-only
			STATUS	current
			::= { hmWanMbus34 39 }

hmWanMbus34VIF11		OBJECT-TYPE
			SYNTAX	INTEGER
			MAX-ACCESS	read-only
			STATUS	current
			::= { hmWanMbus34 40 }

hmWanMbus34Value11		OBJECT-TYPE
			SYNTAX	INTEGER
			MAX-ACCESS	read-only
			STATUS	current
			::= { hmWanMbus34 41 }

hmWanMbus34VIF12		OBJECT-TYPE
			SYNTAX	INTEGER
			MAX-ACCESS	read-only
			STATUS	current
			::= { hmWanMbus34 42 }

hmWanMbus34Value12		OBJECT-TYPE
			SYNTAX	INTEGER
			MAX-ACCESS	read-only
			STATUS	current
			::= { hmWanMbus34 43 }

hmWanMbus34VIF13		OBJECT-TYPE
			SYNTAX	INTEGER
			MAX-ACCESS	read-only
			STATUS	current
			::= { hmWanMbus34 44 }

hmWanMbus34Value13		OBJECT-TYPE
			SYNTAX	INTEGER
			MAX-ACCESS	read-only
			STATUS	current
			::= { hmWanMbus34 45 }

hmWanMbus34VIF14		OBJECT-TYPE
			SYNTAX	INTEGER
			MAX-ACCESS	read-only
			STATUS	current
			::= { hmWanMbus34 46 }

hmWanMbus34Value14		OBJECT-TYPE
			SYNTAX	INTEGER
			MAX-ACCESS	read-only
			STATUS	current
			::= { hmWanMbus34 47 }

hmWanMbus34VIF15		OBJECT-TYPE
			SYNTAX	INTEGER
			MAX-ACCESS	read-only
			STATUS	current
			::= { hmWanMbus34 48 }

hmWanMbus34Value15		OBJECT-TYPE
			SYNTAX	INTEGER
			MAX-ACCESS	read-only
			STATUS	current
			::= { hmWanMbus34 49 }

hmWanMbus34VIF16		OBJECT-TYPE
			SYNTAX	INTEGER
			MAX-ACCESS	read-only
			STATUS	current
			::= { hmWanMbus34 50 }

hmWanMbus34Value16		OBJECT-TYPE
			SYNTAX	INTEGER
			MAX-ACCESS	read-only
			STATUS	current
			::= { hmWanMbus34 51 }

hmWanMbus34VIF17		OBJECT-TYPE
			SYNTAX	INTEGER
			MAX-ACCESS	read-only
			STATUS	current
			::= { hmWanMbus34 52 }

hmWanMbus34Value17		OBJECT-TYPE
			SYNTAX	INTEGER
			MAX-ACCESS	read-only
			STATUS	current
			::= { hmWanMbus34 53 }

hmWanMbus34VIF18		OBJECT-TYPE
			SYNTAX	INTEGER
			MAX-ACCESS	read-only
			STATUS	current
			::= { hmWanMbus34 54 }

hmWanMbus34Value18		OBJECT-TYPE
			SYNTAX	INTEGER
			MAX-ACCESS	read-only
			STATUS	current
			::= { hmWanMbus34 55 }

hmWanMbus34VIF19		OBJECT-TYPE
			SYNTAX	INTEGER
			MAX-ACCESS	read-only
			STATUS	current
			::= { hmWanMbus34 56 }

hmWanMbus34Value19		OBJECT-TYPE
			SYNTAX	INTEGER
			MAX-ACCESS	read-only
			STATUS	current
			::= { hmWanMbus34 57 }

hmWanMbus34VIF1A		OBJECT-TYPE
			SYNTAX	INTEGER
			MAX-ACCESS	read-only
			STATUS	current
			::= { hmWanMbus34 58 }

hmWanMbus34Value1A		OBJECT-TYPE
			SYNTAX	INTEGER
			MAX-ACCESS	read-only
			STATUS	current
			::= { hmWanMbus34 59 }

hmWanMbus34VIF1B		OBJECT-TYPE
			SYNTAX	INTEGER
			MAX-ACCESS	read-only
			STATUS	current
			::= { hmWanMbus34 60 }

hmWanMbus34Value1B		OBJECT-TYPE
			SYNTAX	INTEGER
			MAX-ACCESS	read-only
			STATUS	current
			::= { hmWanMbus34 61 }

hmWanMbus34VIF1C		OBJECT-TYPE
			SYNTAX	INTEGER
			MAX-ACCESS	read-only
			STATUS	current
			::= { hmWanMbus34 62 }

hmWanMbus34Value1C		OBJECT-TYPE
			SYNTAX	INTEGER
			MAX-ACCESS	read-only
			STATUS	current
			::= { hmWanMbus34 63 }

hmWanMbus34VIF1D		OBJECT-TYPE
			SYNTAX	INTEGER
			MAX-ACCESS	read-only
			STATUS	current
			::= { hmWanMbus34 64 }

hmWanMbus34Value1D		OBJECT-TYPE
			SYNTAX	INTEGER
			MAX-ACCESS	read-only
			STATUS	current
			::= { hmWanMbus34 65 }

hmWanMbus34VIF1E		OBJECT-TYPE
			SYNTAX	INTEGER
			MAX-ACCESS	read-only
			STATUS	current
			::= { hmWanMbus34 66 }

hmWanMbus34Value1E		OBJECT-TYPE
			SYNTAX	INTEGER
			MAX-ACCESS	read-only
			STATUS	current
			::= { hmWanMbus34 67 }

hmWanMbus34VIF1F		OBJECT-TYPE
			SYNTAX	INTEGER
			MAX-ACCESS	read-only
			STATUS	current
			::= { hmWanMbus34 68 }

hmWanMbus34Value1F		OBJECT-TYPE
			SYNTAX	INTEGER
			MAX-ACCESS	read-only
			STATUS	current
			::= { hmWanMbus34 69 }

hmWanMbus34VIF20		OBJECT-TYPE
			SYNTAX	INTEGER
			MAX-ACCESS	read-only
			STATUS	current
			::= { hmWanMbus34 70 }

hmWanMbus34Value20		OBJECT-TYPE
			SYNTAX	INTEGER
			MAX-ACCESS	read-only
			STATUS	current
			::= { hmWanMbus34 71 }

hmWanMbus34VIF21		OBJECT-TYPE
			SYNTAX	INTEGER
			MAX-ACCESS	read-only
			STATUS	current
			::= { hmWanMbus34 72 }

hmWanMbus34Value21		OBJECT-TYPE
			SYNTAX	INTEGER
			MAX-ACCESS	read-only
			STATUS	current
			::= { hmWanMbus34 73 }

hmWanMbus34VIF22		OBJECT-TYPE
			SYNTAX	INTEGER
			MAX-ACCESS	read-only
			STATUS	current
			::= { hmWanMbus34 74 }

hmWanMbus34Value22		OBJECT-TYPE
			SYNTAX	INTEGER
			MAX-ACCESS	read-only
			STATUS	current
			::= { hmWanMbus34 75 }

hmWanMbus34VIF23		OBJECT-TYPE
			SYNTAX	INTEGER
			MAX-ACCESS	read-only
			STATUS	current
			::= { hmWanMbus34 76 }

hmWanMbus34Value23		OBJECT-TYPE
			SYNTAX	INTEGER
			MAX-ACCESS	read-only
			STATUS	current
			::= { hmWanMbus34 77 }

hmWanMbus34VIF24		OBJECT-TYPE
			SYNTAX	INTEGER
			MAX-ACCESS	read-only
			STATUS	current
			::= { hmWanMbus34 78 }

hmWanMbus34Value24		OBJECT-TYPE
			SYNTAX	INTEGER
			MAX-ACCESS	read-only
			STATUS	current
			::= { hmWanMbus34 79 }

hmWanMbus34VIF25		OBJECT-TYPE
			SYNTAX	INTEGER
			MAX-ACCESS	read-only
			STATUS	current
			::= { hmWanMbus34 80 }

hmWanMbus34Value25		OBJECT-TYPE
			SYNTAX	INTEGER
			MAX-ACCESS	read-only
			STATUS	current
			::= { hmWanMbus34 81 }

hmWanMbus34VIF26		OBJECT-TYPE
			SYNTAX	INTEGER
			MAX-ACCESS	read-only
			STATUS	current
			::= { hmWanMbus34 82 }

hmWanMbus34Value26		OBJECT-TYPE
			SYNTAX	INTEGER
			MAX-ACCESS	read-only
			STATUS	current
			::= { hmWanMbus34 83 }

hmWanMbus34VIF27		OBJECT-TYPE
			SYNTAX	INTEGER
			MAX-ACCESS	read-only
			STATUS	current
			::= { hmWanMbus34 84 }

hmWanMbus34Value27		OBJECT-TYPE
			SYNTAX	INTEGER
			MAX-ACCESS	read-only
			STATUS	current
			::= { hmWanMbus34 85 }

hmWanMbus34VIF28		OBJECT-TYPE
			SYNTAX	INTEGER
			MAX-ACCESS	read-only
			STATUS	current
			::= { hmWanMbus34 86 }

hmWanMbus34Value28		OBJECT-TYPE
			SYNTAX	INTEGER
			MAX-ACCESS	read-only
			STATUS	current
			::= { hmWanMbus34 87 }

hmWanMbus34VIF29		OBJECT-TYPE
			SYNTAX	INTEGER
			MAX-ACCESS	read-only
			STATUS	current
			::= { hmWanMbus34 88 }

hmWanMbus34Value29		OBJECT-TYPE
			SYNTAX	INTEGER
			MAX-ACCESS	read-only
			STATUS	current
			::= { hmWanMbus34 89 }

hmWanMbus34VIF2A		OBJECT-TYPE
			SYNTAX	INTEGER
			MAX-ACCESS	read-only
			STATUS	current
			::= { hmWanMbus34 90 }

hmWanMbus34Value2A		OBJECT-TYPE
			SYNTAX	INTEGER
			MAX-ACCESS	read-only
			STATUS	current
			::= { hmWanMbus34 91 }

hmWanMbus34VIF2B		OBJECT-TYPE
			SYNTAX	INTEGER
			MAX-ACCESS	read-only
			STATUS	current
			::= { hmWanMbus34 92 }

hmWanMbus34Value2B		OBJECT-TYPE
			SYNTAX	INTEGER
			MAX-ACCESS	read-only
			STATUS	current
			::= { hmWanMbus34 93 }

hmWanMbus34VIF2C		OBJECT-TYPE
			SYNTAX	INTEGER
			MAX-ACCESS	read-only
			STATUS	current
			::= { hmWanMbus34 94 }

hmWanMbus34Value2C		OBJECT-TYPE
			SYNTAX	INTEGER
			MAX-ACCESS	read-only
			STATUS	current
			::= { hmWanMbus34 95 }

hmWanMbus34VIF2D		OBJECT-TYPE
			SYNTAX	INTEGER
			MAX-ACCESS	read-only
			STATUS	current
			::= { hmWanMbus34 96 }

hmWanMbus34Value2D		OBJECT-TYPE
			SYNTAX	INTEGER
			MAX-ACCESS	read-only
			STATUS	current
			::= { hmWanMbus34 97 }

hmWanMbus34VIF2E		OBJECT-TYPE
			SYNTAX	INTEGER
			MAX-ACCESS	read-only
			STATUS	current
			::= { hmWanMbus34 98 }

hmWanMbus34Value2E		OBJECT-TYPE
			SYNTAX	INTEGER
			MAX-ACCESS	read-only
			STATUS	current
			::= { hmWanMbus34 99 }

hmWanMbus34VIF2F		OBJECT-TYPE
			SYNTAX	INTEGER
			MAX-ACCESS	read-only
			STATUS	current
			::= { hmWanMbus34 100 }

hmWanMbus34Value2F		OBJECT-TYPE
			SYNTAX	INTEGER
			MAX-ACCESS	read-only
			STATUS	current
			::= { hmWanMbus34 101 }

hmWanMbus35			OBJECT IDENTIFIER ::= { hmWanMbus 53 }

hmWanMbus35IdNumber		OBJECT-TYPE
			SYNTAX	Gauge32
			MAX-ACCESS	read-only
			STATUS	current
			::= { hmWanMbus35 1 }

hmWanMbus35Manufacturer	OBJECT-TYPE
			SYNTAX	Gauge32
			MAX-ACCESS	read-only
			STATUS	current
			::= { hmWanMbus35 2 }

hmWanMbus35Version		OBJECT-TYPE
			SYNTAX	Gauge32
			MAX-ACCESS	read-only
			STATUS	current
			::= { hmWanMbus35 3 }

hmWanMbus35Medium		OBJECT-TYPE
			SYNTAX	Gauge32
			MAX-ACCESS	read-only
			STATUS	current
			::= { hmWanMbus35 4 }

hmWanMbus35Status		OBJECT-TYPE
			SYNTAX	Gauge32
			MAX-ACCESS	read-only
			STATUS	current
			::= { hmWanMbus35 5 }

hmWanMbus35VIF00		OBJECT-TYPE
			SYNTAX	INTEGER
			MAX-ACCESS	read-only
			STATUS	current
			::= { hmWanMbus35 6 }

hmWanMbus35Value00		OBJECT-TYPE
			SYNTAX	INTEGER
			MAX-ACCESS	read-only
			STATUS	current
			::= { hmWanMbus35 7 }

hmWanMbus35VIF01		OBJECT-TYPE
			SYNTAX	INTEGER
			MAX-ACCESS	read-only
			STATUS	current
			::= { hmWanMbus35 8 }

hmWanMbus35Value01		OBJECT-TYPE
			SYNTAX	INTEGER
			MAX-ACCESS	read-only
			STATUS	current
			::= { hmWanMbus35 9 }

hmWanMbus35VIF02		OBJECT-TYPE
			SYNTAX	INTEGER
			MAX-ACCESS	read-only
			STATUS	current
			::= { hmWanMbus35 10 }

hmWanMbus35Value02		OBJECT-TYPE
			SYNTAX	INTEGER
			MAX-ACCESS	read-only
			STATUS	current
			::= { hmWanMbus35 11 }

hmWanMbus35VIF03		OBJECT-TYPE
			SYNTAX	INTEGER
			MAX-ACCESS	read-only
			STATUS	current
			::= { hmWanMbus35 12 }

hmWanMbus35Value03		OBJECT-TYPE
			SYNTAX	INTEGER
			MAX-ACCESS	read-only
			STATUS	current
			::= { hmWanMbus35 13 }

hmWanMbus35VIF04		OBJECT-TYPE
			SYNTAX	INTEGER
			MAX-ACCESS	read-only
			STATUS	current
			::= { hmWanMbus35 14 }

hmWanMbus35Value04		OBJECT-TYPE
			SYNTAX	INTEGER
			MAX-ACCESS	read-only
			STATUS	current
			::= { hmWanMbus35 15 }

hmWanMbus35VIF05		OBJECT-TYPE
			SYNTAX	INTEGER
			MAX-ACCESS	read-only
			STATUS	current
			::= { hmWanMbus35 16 }

hmWanMbus35Value05		OBJECT-TYPE
			SYNTAX	INTEGER
			MAX-ACCESS	read-only
			STATUS	current
			::= { hmWanMbus35 17 }

hmWanMbus35VIF06		OBJECT-TYPE
			SYNTAX	INTEGER
			MAX-ACCESS	read-only
			STATUS	current
			::= { hmWanMbus35 18 }

hmWanMbus35Value06		OBJECT-TYPE
			SYNTAX	INTEGER
			MAX-ACCESS	read-only
			STATUS	current
			::= { hmWanMbus35 19 }

hmWanMbus35VIF07		OBJECT-TYPE
			SYNTAX	INTEGER
			MAX-ACCESS	read-only
			STATUS	current
			::= { hmWanMbus35 20 }

hmWanMbus35Value07		OBJECT-TYPE
			SYNTAX	INTEGER
			MAX-ACCESS	read-only
			STATUS	current
			::= { hmWanMbus35 21 }

hmWanMbus35VIF08		OBJECT-TYPE
			SYNTAX	INTEGER
			MAX-ACCESS	read-only
			STATUS	current
			::= { hmWanMbus35 22 }

hmWanMbus35Value08		OBJECT-TYPE
			SYNTAX	INTEGER
			MAX-ACCESS	read-only
			STATUS	current
			::= { hmWanMbus35 23 }

hmWanMbus35VIF09		OBJECT-TYPE
			SYNTAX	INTEGER
			MAX-ACCESS	read-only
			STATUS	current
			::= { hmWanMbus35 24 }

hmWanMbus35Value09		OBJECT-TYPE
			SYNTAX	INTEGER
			MAX-ACCESS	read-only
			STATUS	current
			::= { hmWanMbus35 25 }

hmWanMbus35VIF0A		OBJECT-TYPE
			SYNTAX	INTEGER
			MAX-ACCESS	read-only
			STATUS	current
			::= { hmWanMbus35 26 }

hmWanMbus35Value0A		OBJECT-TYPE
			SYNTAX	INTEGER
			MAX-ACCESS	read-only
			STATUS	current
			::= { hmWanMbus35 27 }

hmWanMbus35VIF0B		OBJECT-TYPE
			SYNTAX	INTEGER
			MAX-ACCESS	read-only
			STATUS	current
			::= { hmWanMbus35 28 }

hmWanMbus35Value0B		OBJECT-TYPE
			SYNTAX	INTEGER
			MAX-ACCESS	read-only
			STATUS	current
			::= { hmWanMbus35 29 }

hmWanMbus35VIF0C		OBJECT-TYPE
			SYNTAX	INTEGER
			MAX-ACCESS	read-only
			STATUS	current
			::= { hmWanMbus35 30 }

hmWanMbus35Value0C		OBJECT-TYPE
			SYNTAX	INTEGER
			MAX-ACCESS	read-only
			STATUS	current
			::= { hmWanMbus35 31 }

hmWanMbus35VIF0D		OBJECT-TYPE
			SYNTAX	INTEGER
			MAX-ACCESS	read-only
			STATUS	current
			::= { hmWanMbus35 32 }

hmWanMbus35Value0D		OBJECT-TYPE
			SYNTAX	INTEGER
			MAX-ACCESS	read-only
			STATUS	current
			::= { hmWanMbus35 33 }

hmWanMbus35VIF0E		OBJECT-TYPE
			SYNTAX	INTEGER
			MAX-ACCESS	read-only
			STATUS	current
			::= { hmWanMbus35 34 }

hmWanMbus35Value0E		OBJECT-TYPE
			SYNTAX	INTEGER
			MAX-ACCESS	read-only
			STATUS	current
			::= { hmWanMbus35 35 }

hmWanMbus35VIF0F		OBJECT-TYPE
			SYNTAX	INTEGER
			MAX-ACCESS	read-only
			STATUS	current
			::= { hmWanMbus35 36 }

hmWanMbus35Value0F		OBJECT-TYPE
			SYNTAX	INTEGER
			MAX-ACCESS	read-only
			STATUS	current
			::= { hmWanMbus35 37 }

hmWanMbus35VIF10		OBJECT-TYPE
			SYNTAX	INTEGER
			MAX-ACCESS	read-only
			STATUS	current
			::= { hmWanMbus35 38 }

hmWanMbus35Value10		OBJECT-TYPE
			SYNTAX	INTEGER
			MAX-ACCESS	read-only
			STATUS	current
			::= { hmWanMbus35 39 }

hmWanMbus35VIF11		OBJECT-TYPE
			SYNTAX	INTEGER
			MAX-ACCESS	read-only
			STATUS	current
			::= { hmWanMbus35 40 }

hmWanMbus35Value11		OBJECT-TYPE
			SYNTAX	INTEGER
			MAX-ACCESS	read-only
			STATUS	current
			::= { hmWanMbus35 41 }

hmWanMbus35VIF12		OBJECT-TYPE
			SYNTAX	INTEGER
			MAX-ACCESS	read-only
			STATUS	current
			::= { hmWanMbus35 42 }

hmWanMbus35Value12		OBJECT-TYPE
			SYNTAX	INTEGER
			MAX-ACCESS	read-only
			STATUS	current
			::= { hmWanMbus35 43 }

hmWanMbus35VIF13		OBJECT-TYPE
			SYNTAX	INTEGER
			MAX-ACCESS	read-only
			STATUS	current
			::= { hmWanMbus35 44 }

hmWanMbus35Value13		OBJECT-TYPE
			SYNTAX	INTEGER
			MAX-ACCESS	read-only
			STATUS	current
			::= { hmWanMbus35 45 }

hmWanMbus35VIF14		OBJECT-TYPE
			SYNTAX	INTEGER
			MAX-ACCESS	read-only
			STATUS	current
			::= { hmWanMbus35 46 }

hmWanMbus35Value14		OBJECT-TYPE
			SYNTAX	INTEGER
			MAX-ACCESS	read-only
			STATUS	current
			::= { hmWanMbus35 47 }

hmWanMbus35VIF15		OBJECT-TYPE
			SYNTAX	INTEGER
			MAX-ACCESS	read-only
			STATUS	current
			::= { hmWanMbus35 48 }

hmWanMbus35Value15		OBJECT-TYPE
			SYNTAX	INTEGER
			MAX-ACCESS	read-only
			STATUS	current
			::= { hmWanMbus35 49 }

hmWanMbus35VIF16		OBJECT-TYPE
			SYNTAX	INTEGER
			MAX-ACCESS	read-only
			STATUS	current
			::= { hmWanMbus35 50 }

hmWanMbus35Value16		OBJECT-TYPE
			SYNTAX	INTEGER
			MAX-ACCESS	read-only
			STATUS	current
			::= { hmWanMbus35 51 }

hmWanMbus35VIF17		OBJECT-TYPE
			SYNTAX	INTEGER
			MAX-ACCESS	read-only
			STATUS	current
			::= { hmWanMbus35 52 }

hmWanMbus35Value17		OBJECT-TYPE
			SYNTAX	INTEGER
			MAX-ACCESS	read-only
			STATUS	current
			::= { hmWanMbus35 53 }

hmWanMbus35VIF18		OBJECT-TYPE
			SYNTAX	INTEGER
			MAX-ACCESS	read-only
			STATUS	current
			::= { hmWanMbus35 54 }

hmWanMbus35Value18		OBJECT-TYPE
			SYNTAX	INTEGER
			MAX-ACCESS	read-only
			STATUS	current
			::= { hmWanMbus35 55 }

hmWanMbus35VIF19		OBJECT-TYPE
			SYNTAX	INTEGER
			MAX-ACCESS	read-only
			STATUS	current
			::= { hmWanMbus35 56 }

hmWanMbus35Value19		OBJECT-TYPE
			SYNTAX	INTEGER
			MAX-ACCESS	read-only
			STATUS	current
			::= { hmWanMbus35 57 }

hmWanMbus35VIF1A		OBJECT-TYPE
			SYNTAX	INTEGER
			MAX-ACCESS	read-only
			STATUS	current
			::= { hmWanMbus35 58 }

hmWanMbus35Value1A		OBJECT-TYPE
			SYNTAX	INTEGER
			MAX-ACCESS	read-only
			STATUS	current
			::= { hmWanMbus35 59 }

hmWanMbus35VIF1B		OBJECT-TYPE
			SYNTAX	INTEGER
			MAX-ACCESS	read-only
			STATUS	current
			::= { hmWanMbus35 60 }

hmWanMbus35Value1B		OBJECT-TYPE
			SYNTAX	INTEGER
			MAX-ACCESS	read-only
			STATUS	current
			::= { hmWanMbus35 61 }

hmWanMbus35VIF1C		OBJECT-TYPE
			SYNTAX	INTEGER
			MAX-ACCESS	read-only
			STATUS	current
			::= { hmWanMbus35 62 }

hmWanMbus35Value1C		OBJECT-TYPE
			SYNTAX	INTEGER
			MAX-ACCESS	read-only
			STATUS	current
			::= { hmWanMbus35 63 }

hmWanMbus35VIF1D		OBJECT-TYPE
			SYNTAX	INTEGER
			MAX-ACCESS	read-only
			STATUS	current
			::= { hmWanMbus35 64 }

hmWanMbus35Value1D		OBJECT-TYPE
			SYNTAX	INTEGER
			MAX-ACCESS	read-only
			STATUS	current
			::= { hmWanMbus35 65 }

hmWanMbus35VIF1E		OBJECT-TYPE
			SYNTAX	INTEGER
			MAX-ACCESS	read-only
			STATUS	current
			::= { hmWanMbus35 66 }

hmWanMbus35Value1E		OBJECT-TYPE
			SYNTAX	INTEGER
			MAX-ACCESS	read-only
			STATUS	current
			::= { hmWanMbus35 67 }

hmWanMbus35VIF1F		OBJECT-TYPE
			SYNTAX	INTEGER
			MAX-ACCESS	read-only
			STATUS	current
			::= { hmWanMbus35 68 }

hmWanMbus35Value1F		OBJECT-TYPE
			SYNTAX	INTEGER
			MAX-ACCESS	read-only
			STATUS	current
			::= { hmWanMbus35 69 }

hmWanMbus35VIF20		OBJECT-TYPE
			SYNTAX	INTEGER
			MAX-ACCESS	read-only
			STATUS	current
			::= { hmWanMbus35 70 }

hmWanMbus35Value20		OBJECT-TYPE
			SYNTAX	INTEGER
			MAX-ACCESS	read-only
			STATUS	current
			::= { hmWanMbus35 71 }

hmWanMbus35VIF21		OBJECT-TYPE
			SYNTAX	INTEGER
			MAX-ACCESS	read-only
			STATUS	current
			::= { hmWanMbus35 72 }

hmWanMbus35Value21		OBJECT-TYPE
			SYNTAX	INTEGER
			MAX-ACCESS	read-only
			STATUS	current
			::= { hmWanMbus35 73 }

hmWanMbus35VIF22		OBJECT-TYPE
			SYNTAX	INTEGER
			MAX-ACCESS	read-only
			STATUS	current
			::= { hmWanMbus35 74 }

hmWanMbus35Value22		OBJECT-TYPE
			SYNTAX	INTEGER
			MAX-ACCESS	read-only
			STATUS	current
			::= { hmWanMbus35 75 }

hmWanMbus35VIF23		OBJECT-TYPE
			SYNTAX	INTEGER
			MAX-ACCESS	read-only
			STATUS	current
			::= { hmWanMbus35 76 }

hmWanMbus35Value23		OBJECT-TYPE
			SYNTAX	INTEGER
			MAX-ACCESS	read-only
			STATUS	current
			::= { hmWanMbus35 77 }

hmWanMbus35VIF24		OBJECT-TYPE
			SYNTAX	INTEGER
			MAX-ACCESS	read-only
			STATUS	current
			::= { hmWanMbus35 78 }

hmWanMbus35Value24		OBJECT-TYPE
			SYNTAX	INTEGER
			MAX-ACCESS	read-only
			STATUS	current
			::= { hmWanMbus35 79 }

hmWanMbus35VIF25		OBJECT-TYPE
			SYNTAX	INTEGER
			MAX-ACCESS	read-only
			STATUS	current
			::= { hmWanMbus35 80 }

hmWanMbus35Value25		OBJECT-TYPE
			SYNTAX	INTEGER
			MAX-ACCESS	read-only
			STATUS	current
			::= { hmWanMbus35 81 }

hmWanMbus35VIF26		OBJECT-TYPE
			SYNTAX	INTEGER
			MAX-ACCESS	read-only
			STATUS	current
			::= { hmWanMbus35 82 }

hmWanMbus35Value26		OBJECT-TYPE
			SYNTAX	INTEGER
			MAX-ACCESS	read-only
			STATUS	current
			::= { hmWanMbus35 83 }

hmWanMbus35VIF27		OBJECT-TYPE
			SYNTAX	INTEGER
			MAX-ACCESS	read-only
			STATUS	current
			::= { hmWanMbus35 84 }

hmWanMbus35Value27		OBJECT-TYPE
			SYNTAX	INTEGER
			MAX-ACCESS	read-only
			STATUS	current
			::= { hmWanMbus35 85 }

hmWanMbus35VIF28		OBJECT-TYPE
			SYNTAX	INTEGER
			MAX-ACCESS	read-only
			STATUS	current
			::= { hmWanMbus35 86 }

hmWanMbus35Value28		OBJECT-TYPE
			SYNTAX	INTEGER
			MAX-ACCESS	read-only
			STATUS	current
			::= { hmWanMbus35 87 }

hmWanMbus35VIF29		OBJECT-TYPE
			SYNTAX	INTEGER
			MAX-ACCESS	read-only
			STATUS	current
			::= { hmWanMbus35 88 }

hmWanMbus35Value29		OBJECT-TYPE
			SYNTAX	INTEGER
			MAX-ACCESS	read-only
			STATUS	current
			::= { hmWanMbus35 89 }

hmWanMbus35VIF2A		OBJECT-TYPE
			SYNTAX	INTEGER
			MAX-ACCESS	read-only
			STATUS	current
			::= { hmWanMbus35 90 }

hmWanMbus35Value2A		OBJECT-TYPE
			SYNTAX	INTEGER
			MAX-ACCESS	read-only
			STATUS	current
			::= { hmWanMbus35 91 }

hmWanMbus35VIF2B		OBJECT-TYPE
			SYNTAX	INTEGER
			MAX-ACCESS	read-only
			STATUS	current
			::= { hmWanMbus35 92 }

hmWanMbus35Value2B		OBJECT-TYPE
			SYNTAX	INTEGER
			MAX-ACCESS	read-only
			STATUS	current
			::= { hmWanMbus35 93 }

hmWanMbus35VIF2C		OBJECT-TYPE
			SYNTAX	INTEGER
			MAX-ACCESS	read-only
			STATUS	current
			::= { hmWanMbus35 94 }

hmWanMbus35Value2C		OBJECT-TYPE
			SYNTAX	INTEGER
			MAX-ACCESS	read-only
			STATUS	current
			::= { hmWanMbus35 95 }

hmWanMbus35VIF2D		OBJECT-TYPE
			SYNTAX	INTEGER
			MAX-ACCESS	read-only
			STATUS	current
			::= { hmWanMbus35 96 }

hmWanMbus35Value2D		OBJECT-TYPE
			SYNTAX	INTEGER
			MAX-ACCESS	read-only
			STATUS	current
			::= { hmWanMbus35 97 }

hmWanMbus35VIF2E		OBJECT-TYPE
			SYNTAX	INTEGER
			MAX-ACCESS	read-only
			STATUS	current
			::= { hmWanMbus35 98 }

hmWanMbus35Value2E		OBJECT-TYPE
			SYNTAX	INTEGER
			MAX-ACCESS	read-only
			STATUS	current
			::= { hmWanMbus35 99 }

hmWanMbus35VIF2F		OBJECT-TYPE
			SYNTAX	INTEGER
			MAX-ACCESS	read-only
			STATUS	current
			::= { hmWanMbus35 100 }

hmWanMbus35Value2F		OBJECT-TYPE
			SYNTAX	INTEGER
			MAX-ACCESS	read-only
			STATUS	current
			::= { hmWanMbus35 101 }

hmWanMbus36			OBJECT IDENTIFIER ::= { hmWanMbus 54 }

hmWanMbus36IdNumber		OBJECT-TYPE
			SYNTAX	Gauge32
			MAX-ACCESS	read-only
			STATUS	current
			::= { hmWanMbus36 1 }

hmWanMbus36Manufacturer	OBJECT-TYPE
			SYNTAX	Gauge32
			MAX-ACCESS	read-only
			STATUS	current
			::= { hmWanMbus36 2 }

hmWanMbus36Version		OBJECT-TYPE
			SYNTAX	Gauge32
			MAX-ACCESS	read-only
			STATUS	current
			::= { hmWanMbus36 3 }

hmWanMbus36Medium		OBJECT-TYPE
			SYNTAX	Gauge32
			MAX-ACCESS	read-only
			STATUS	current
			::= { hmWanMbus36 4 }

hmWanMbus36Status		OBJECT-TYPE
			SYNTAX	Gauge32
			MAX-ACCESS	read-only
			STATUS	current
			::= { hmWanMbus36 5 }

hmWanMbus36VIF00		OBJECT-TYPE
			SYNTAX	INTEGER
			MAX-ACCESS	read-only
			STATUS	current
			::= { hmWanMbus36 6 }

hmWanMbus36Value00		OBJECT-TYPE
			SYNTAX	INTEGER
			MAX-ACCESS	read-only
			STATUS	current
			::= { hmWanMbus36 7 }

hmWanMbus36VIF01		OBJECT-TYPE
			SYNTAX	INTEGER
			MAX-ACCESS	read-only
			STATUS	current
			::= { hmWanMbus36 8 }

hmWanMbus36Value01		OBJECT-TYPE
			SYNTAX	INTEGER
			MAX-ACCESS	read-only
			STATUS	current
			::= { hmWanMbus36 9 }

hmWanMbus36VIF02		OBJECT-TYPE
			SYNTAX	INTEGER
			MAX-ACCESS	read-only
			STATUS	current
			::= { hmWanMbus36 10 }

hmWanMbus36Value02		OBJECT-TYPE
			SYNTAX	INTEGER
			MAX-ACCESS	read-only
			STATUS	current
			::= { hmWanMbus36 11 }

hmWanMbus36VIF03		OBJECT-TYPE
			SYNTAX	INTEGER
			MAX-ACCESS	read-only
			STATUS	current
			::= { hmWanMbus36 12 }

hmWanMbus36Value03		OBJECT-TYPE
			SYNTAX	INTEGER
			MAX-ACCESS	read-only
			STATUS	current
			::= { hmWanMbus36 13 }

hmWanMbus36VIF04		OBJECT-TYPE
			SYNTAX	INTEGER
			MAX-ACCESS	read-only
			STATUS	current
			::= { hmWanMbus36 14 }

hmWanMbus36Value04		OBJECT-TYPE
			SYNTAX	INTEGER
			MAX-ACCESS	read-only
			STATUS	current
			::= { hmWanMbus36 15 }

hmWanMbus36VIF05		OBJECT-TYPE
			SYNTAX	INTEGER
			MAX-ACCESS	read-only
			STATUS	current
			::= { hmWanMbus36 16 }

hmWanMbus36Value05		OBJECT-TYPE
			SYNTAX	INTEGER
			MAX-ACCESS	read-only
			STATUS	current
			::= { hmWanMbus36 17 }

hmWanMbus36VIF06		OBJECT-TYPE
			SYNTAX	INTEGER
			MAX-ACCESS	read-only
			STATUS	current
			::= { hmWanMbus36 18 }

hmWanMbus36Value06		OBJECT-TYPE
			SYNTAX	INTEGER
			MAX-ACCESS	read-only
			STATUS	current
			::= { hmWanMbus36 19 }

hmWanMbus36VIF07		OBJECT-TYPE
			SYNTAX	INTEGER
			MAX-ACCESS	read-only
			STATUS	current
			::= { hmWanMbus36 20 }

hmWanMbus36Value07		OBJECT-TYPE
			SYNTAX	INTEGER
			MAX-ACCESS	read-only
			STATUS	current
			::= { hmWanMbus36 21 }

hmWanMbus36VIF08		OBJECT-TYPE
			SYNTAX	INTEGER
			MAX-ACCESS	read-only
			STATUS	current
			::= { hmWanMbus36 22 }

hmWanMbus36Value08		OBJECT-TYPE
			SYNTAX	INTEGER
			MAX-ACCESS	read-only
			STATUS	current
			::= { hmWanMbus36 23 }

hmWanMbus36VIF09		OBJECT-TYPE
			SYNTAX	INTEGER
			MAX-ACCESS	read-only
			STATUS	current
			::= { hmWanMbus36 24 }

hmWanMbus36Value09		OBJECT-TYPE
			SYNTAX	INTEGER
			MAX-ACCESS	read-only
			STATUS	current
			::= { hmWanMbus36 25 }

hmWanMbus36VIF0A		OBJECT-TYPE
			SYNTAX	INTEGER
			MAX-ACCESS	read-only
			STATUS	current
			::= { hmWanMbus36 26 }

hmWanMbus36Value0A		OBJECT-TYPE
			SYNTAX	INTEGER
			MAX-ACCESS	read-only
			STATUS	current
			::= { hmWanMbus36 27 }

hmWanMbus36VIF0B		OBJECT-TYPE
			SYNTAX	INTEGER
			MAX-ACCESS	read-only
			STATUS	current
			::= { hmWanMbus36 28 }

hmWanMbus36Value0B		OBJECT-TYPE
			SYNTAX	INTEGER
			MAX-ACCESS	read-only
			STATUS	current
			::= { hmWanMbus36 29 }

hmWanMbus36VIF0C		OBJECT-TYPE
			SYNTAX	INTEGER
			MAX-ACCESS	read-only
			STATUS	current
			::= { hmWanMbus36 30 }

hmWanMbus36Value0C		OBJECT-TYPE
			SYNTAX	INTEGER
			MAX-ACCESS	read-only
			STATUS	current
			::= { hmWanMbus36 31 }

hmWanMbus36VIF0D		OBJECT-TYPE
			SYNTAX	INTEGER
			MAX-ACCESS	read-only
			STATUS	current
			::= { hmWanMbus36 32 }

hmWanMbus36Value0D		OBJECT-TYPE
			SYNTAX	INTEGER
			MAX-ACCESS	read-only
			STATUS	current
			::= { hmWanMbus36 33 }

hmWanMbus36VIF0E		OBJECT-TYPE
			SYNTAX	INTEGER
			MAX-ACCESS	read-only
			STATUS	current
			::= { hmWanMbus36 34 }

hmWanMbus36Value0E		OBJECT-TYPE
			SYNTAX	INTEGER
			MAX-ACCESS	read-only
			STATUS	current
			::= { hmWanMbus36 35 }

hmWanMbus36VIF0F		OBJECT-TYPE
			SYNTAX	INTEGER
			MAX-ACCESS	read-only
			STATUS	current
			::= { hmWanMbus36 36 }

hmWanMbus36Value0F		OBJECT-TYPE
			SYNTAX	INTEGER
			MAX-ACCESS	read-only
			STATUS	current
			::= { hmWanMbus36 37 }

hmWanMbus36VIF10		OBJECT-TYPE
			SYNTAX	INTEGER
			MAX-ACCESS	read-only
			STATUS	current
			::= { hmWanMbus36 38 }

hmWanMbus36Value10		OBJECT-TYPE
			SYNTAX	INTEGER
			MAX-ACCESS	read-only
			STATUS	current
			::= { hmWanMbus36 39 }

hmWanMbus36VIF11		OBJECT-TYPE
			SYNTAX	INTEGER
			MAX-ACCESS	read-only
			STATUS	current
			::= { hmWanMbus36 40 }

hmWanMbus36Value11		OBJECT-TYPE
			SYNTAX	INTEGER
			MAX-ACCESS	read-only
			STATUS	current
			::= { hmWanMbus36 41 }

hmWanMbus36VIF12		OBJECT-TYPE
			SYNTAX	INTEGER
			MAX-ACCESS	read-only
			STATUS	current
			::= { hmWanMbus36 42 }

hmWanMbus36Value12		OBJECT-TYPE
			SYNTAX	INTEGER
			MAX-ACCESS	read-only
			STATUS	current
			::= { hmWanMbus36 43 }

hmWanMbus36VIF13		OBJECT-TYPE
			SYNTAX	INTEGER
			MAX-ACCESS	read-only
			STATUS	current
			::= { hmWanMbus36 44 }

hmWanMbus36Value13		OBJECT-TYPE
			SYNTAX	INTEGER
			MAX-ACCESS	read-only
			STATUS	current
			::= { hmWanMbus36 45 }

hmWanMbus36VIF14		OBJECT-TYPE
			SYNTAX	INTEGER
			MAX-ACCESS	read-only
			STATUS	current
			::= { hmWanMbus36 46 }

hmWanMbus36Value14		OBJECT-TYPE
			SYNTAX	INTEGER
			MAX-ACCESS	read-only
			STATUS	current
			::= { hmWanMbus36 47 }

hmWanMbus36VIF15		OBJECT-TYPE
			SYNTAX	INTEGER
			MAX-ACCESS	read-only
			STATUS	current
			::= { hmWanMbus36 48 }

hmWanMbus36Value15		OBJECT-TYPE
			SYNTAX	INTEGER
			MAX-ACCESS	read-only
			STATUS	current
			::= { hmWanMbus36 49 }

hmWanMbus36VIF16		OBJECT-TYPE
			SYNTAX	INTEGER
			MAX-ACCESS	read-only
			STATUS	current
			::= { hmWanMbus36 50 }

hmWanMbus36Value16		OBJECT-TYPE
			SYNTAX	INTEGER
			MAX-ACCESS	read-only
			STATUS	current
			::= { hmWanMbus36 51 }

hmWanMbus36VIF17		OBJECT-TYPE
			SYNTAX	INTEGER
			MAX-ACCESS	read-only
			STATUS	current
			::= { hmWanMbus36 52 }

hmWanMbus36Value17		OBJECT-TYPE
			SYNTAX	INTEGER
			MAX-ACCESS	read-only
			STATUS	current
			::= { hmWanMbus36 53 }

hmWanMbus36VIF18		OBJECT-TYPE
			SYNTAX	INTEGER
			MAX-ACCESS	read-only
			STATUS	current
			::= { hmWanMbus36 54 }

hmWanMbus36Value18		OBJECT-TYPE
			SYNTAX	INTEGER
			MAX-ACCESS	read-only
			STATUS	current
			::= { hmWanMbus36 55 }

hmWanMbus36VIF19		OBJECT-TYPE
			SYNTAX	INTEGER
			MAX-ACCESS	read-only
			STATUS	current
			::= { hmWanMbus36 56 }

hmWanMbus36Value19		OBJECT-TYPE
			SYNTAX	INTEGER
			MAX-ACCESS	read-only
			STATUS	current
			::= { hmWanMbus36 57 }

hmWanMbus36VIF1A		OBJECT-TYPE
			SYNTAX	INTEGER
			MAX-ACCESS	read-only
			STATUS	current
			::= { hmWanMbus36 58 }

hmWanMbus36Value1A		OBJECT-TYPE
			SYNTAX	INTEGER
			MAX-ACCESS	read-only
			STATUS	current
			::= { hmWanMbus36 59 }

hmWanMbus36VIF1B		OBJECT-TYPE
			SYNTAX	INTEGER
			MAX-ACCESS	read-only
			STATUS	current
			::= { hmWanMbus36 60 }

hmWanMbus36Value1B		OBJECT-TYPE
			SYNTAX	INTEGER
			MAX-ACCESS	read-only
			STATUS	current
			::= { hmWanMbus36 61 }

hmWanMbus36VIF1C		OBJECT-TYPE
			SYNTAX	INTEGER
			MAX-ACCESS	read-only
			STATUS	current
			::= { hmWanMbus36 62 }

hmWanMbus36Value1C		OBJECT-TYPE
			SYNTAX	INTEGER
			MAX-ACCESS	read-only
			STATUS	current
			::= { hmWanMbus36 63 }

hmWanMbus36VIF1D		OBJECT-TYPE
			SYNTAX	INTEGER
			MAX-ACCESS	read-only
			STATUS	current
			::= { hmWanMbus36 64 }

hmWanMbus36Value1D		OBJECT-TYPE
			SYNTAX	INTEGER
			MAX-ACCESS	read-only
			STATUS	current
			::= { hmWanMbus36 65 }

hmWanMbus36VIF1E		OBJECT-TYPE
			SYNTAX	INTEGER
			MAX-ACCESS	read-only
			STATUS	current
			::= { hmWanMbus36 66 }

hmWanMbus36Value1E		OBJECT-TYPE
			SYNTAX	INTEGER
			MAX-ACCESS	read-only
			STATUS	current
			::= { hmWanMbus36 67 }

hmWanMbus36VIF1F		OBJECT-TYPE
			SYNTAX	INTEGER
			MAX-ACCESS	read-only
			STATUS	current
			::= { hmWanMbus36 68 }

hmWanMbus36Value1F		OBJECT-TYPE
			SYNTAX	INTEGER
			MAX-ACCESS	read-only
			STATUS	current
			::= { hmWanMbus36 69 }

hmWanMbus36VIF20		OBJECT-TYPE
			SYNTAX	INTEGER
			MAX-ACCESS	read-only
			STATUS	current
			::= { hmWanMbus36 70 }

hmWanMbus36Value20		OBJECT-TYPE
			SYNTAX	INTEGER
			MAX-ACCESS	read-only
			STATUS	current
			::= { hmWanMbus36 71 }

hmWanMbus36VIF21		OBJECT-TYPE
			SYNTAX	INTEGER
			MAX-ACCESS	read-only
			STATUS	current
			::= { hmWanMbus36 72 }

hmWanMbus36Value21		OBJECT-TYPE
			SYNTAX	INTEGER
			MAX-ACCESS	read-only
			STATUS	current
			::= { hmWanMbus36 73 }

hmWanMbus36VIF22		OBJECT-TYPE
			SYNTAX	INTEGER
			MAX-ACCESS	read-only
			STATUS	current
			::= { hmWanMbus36 74 }

hmWanMbus36Value22		OBJECT-TYPE
			SYNTAX	INTEGER
			MAX-ACCESS	read-only
			STATUS	current
			::= { hmWanMbus36 75 }

hmWanMbus36VIF23		OBJECT-TYPE
			SYNTAX	INTEGER
			MAX-ACCESS	read-only
			STATUS	current
			::= { hmWanMbus36 76 }

hmWanMbus36Value23		OBJECT-TYPE
			SYNTAX	INTEGER
			MAX-ACCESS	read-only
			STATUS	current
			::= { hmWanMbus36 77 }

hmWanMbus36VIF24		OBJECT-TYPE
			SYNTAX	INTEGER
			MAX-ACCESS	read-only
			STATUS	current
			::= { hmWanMbus36 78 }

hmWanMbus36Value24		OBJECT-TYPE
			SYNTAX	INTEGER
			MAX-ACCESS	read-only
			STATUS	current
			::= { hmWanMbus36 79 }

hmWanMbus36VIF25		OBJECT-TYPE
			SYNTAX	INTEGER
			MAX-ACCESS	read-only
			STATUS	current
			::= { hmWanMbus36 80 }

hmWanMbus36Value25		OBJECT-TYPE
			SYNTAX	INTEGER
			MAX-ACCESS	read-only
			STATUS	current
			::= { hmWanMbus36 81 }

hmWanMbus36VIF26		OBJECT-TYPE
			SYNTAX	INTEGER
			MAX-ACCESS	read-only
			STATUS	current
			::= { hmWanMbus36 82 }

hmWanMbus36Value26		OBJECT-TYPE
			SYNTAX	INTEGER
			MAX-ACCESS	read-only
			STATUS	current
			::= { hmWanMbus36 83 }

hmWanMbus36VIF27		OBJECT-TYPE
			SYNTAX	INTEGER
			MAX-ACCESS	read-only
			STATUS	current
			::= { hmWanMbus36 84 }

hmWanMbus36Value27		OBJECT-TYPE
			SYNTAX	INTEGER
			MAX-ACCESS	read-only
			STATUS	current
			::= { hmWanMbus36 85 }

hmWanMbus36VIF28		OBJECT-TYPE
			SYNTAX	INTEGER
			MAX-ACCESS	read-only
			STATUS	current
			::= { hmWanMbus36 86 }

hmWanMbus36Value28		OBJECT-TYPE
			SYNTAX	INTEGER
			MAX-ACCESS	read-only
			STATUS	current
			::= { hmWanMbus36 87 }

hmWanMbus36VIF29		OBJECT-TYPE
			SYNTAX	INTEGER
			MAX-ACCESS	read-only
			STATUS	current
			::= { hmWanMbus36 88 }

hmWanMbus36Value29		OBJECT-TYPE
			SYNTAX	INTEGER
			MAX-ACCESS	read-only
			STATUS	current
			::= { hmWanMbus36 89 }

hmWanMbus36VIF2A		OBJECT-TYPE
			SYNTAX	INTEGER
			MAX-ACCESS	read-only
			STATUS	current
			::= { hmWanMbus36 90 }

hmWanMbus36Value2A		OBJECT-TYPE
			SYNTAX	INTEGER
			MAX-ACCESS	read-only
			STATUS	current
			::= { hmWanMbus36 91 }

hmWanMbus36VIF2B		OBJECT-TYPE
			SYNTAX	INTEGER
			MAX-ACCESS	read-only
			STATUS	current
			::= { hmWanMbus36 92 }

hmWanMbus36Value2B		OBJECT-TYPE
			SYNTAX	INTEGER
			MAX-ACCESS	read-only
			STATUS	current
			::= { hmWanMbus36 93 }

hmWanMbus36VIF2C		OBJECT-TYPE
			SYNTAX	INTEGER
			MAX-ACCESS	read-only
			STATUS	current
			::= { hmWanMbus36 94 }

hmWanMbus36Value2C		OBJECT-TYPE
			SYNTAX	INTEGER
			MAX-ACCESS	read-only
			STATUS	current
			::= { hmWanMbus36 95 }

hmWanMbus36VIF2D		OBJECT-TYPE
			SYNTAX	INTEGER
			MAX-ACCESS	read-only
			STATUS	current
			::= { hmWanMbus36 96 }

hmWanMbus36Value2D		OBJECT-TYPE
			SYNTAX	INTEGER
			MAX-ACCESS	read-only
			STATUS	current
			::= { hmWanMbus36 97 }

hmWanMbus36VIF2E		OBJECT-TYPE
			SYNTAX	INTEGER
			MAX-ACCESS	read-only
			STATUS	current
			::= { hmWanMbus36 98 }

hmWanMbus36Value2E		OBJECT-TYPE
			SYNTAX	INTEGER
			MAX-ACCESS	read-only
			STATUS	current
			::= { hmWanMbus36 99 }

hmWanMbus36VIF2F		OBJECT-TYPE
			SYNTAX	INTEGER
			MAX-ACCESS	read-only
			STATUS	current
			::= { hmWanMbus36 100 }

hmWanMbus36Value2F		OBJECT-TYPE
			SYNTAX	INTEGER
			MAX-ACCESS	read-only
			STATUS	current
			::= { hmWanMbus36 101 }

hmWanMbus37			OBJECT IDENTIFIER ::= { hmWanMbus 55 }

hmWanMbus37IdNumber		OBJECT-TYPE
			SYNTAX	Gauge32
			MAX-ACCESS	read-only
			STATUS	current
			::= { hmWanMbus37 1 }

hmWanMbus37Manufacturer	OBJECT-TYPE
			SYNTAX	Gauge32
			MAX-ACCESS	read-only
			STATUS	current
			::= { hmWanMbus37 2 }

hmWanMbus37Version		OBJECT-TYPE
			SYNTAX	Gauge32
			MAX-ACCESS	read-only
			STATUS	current
			::= { hmWanMbus37 3 }

hmWanMbus37Medium		OBJECT-TYPE
			SYNTAX	Gauge32
			MAX-ACCESS	read-only
			STATUS	current
			::= { hmWanMbus37 4 }

hmWanMbus37Status		OBJECT-TYPE
			SYNTAX	Gauge32
			MAX-ACCESS	read-only
			STATUS	current
			::= { hmWanMbus37 5 }

hmWanMbus37VIF00		OBJECT-TYPE
			SYNTAX	INTEGER
			MAX-ACCESS	read-only
			STATUS	current
			::= { hmWanMbus37 6 }

hmWanMbus37Value00		OBJECT-TYPE
			SYNTAX	INTEGER
			MAX-ACCESS	read-only
			STATUS	current
			::= { hmWanMbus37 7 }

hmWanMbus37VIF01		OBJECT-TYPE
			SYNTAX	INTEGER
			MAX-ACCESS	read-only
			STATUS	current
			::= { hmWanMbus37 8 }

hmWanMbus37Value01		OBJECT-TYPE
			SYNTAX	INTEGER
			MAX-ACCESS	read-only
			STATUS	current
			::= { hmWanMbus37 9 }

hmWanMbus37VIF02		OBJECT-TYPE
			SYNTAX	INTEGER
			MAX-ACCESS	read-only
			STATUS	current
			::= { hmWanMbus37 10 }

hmWanMbus37Value02		OBJECT-TYPE
			SYNTAX	INTEGER
			MAX-ACCESS	read-only
			STATUS	current
			::= { hmWanMbus37 11 }

hmWanMbus37VIF03		OBJECT-TYPE
			SYNTAX	INTEGER
			MAX-ACCESS	read-only
			STATUS	current
			::= { hmWanMbus37 12 }

hmWanMbus37Value03		OBJECT-TYPE
			SYNTAX	INTEGER
			MAX-ACCESS	read-only
			STATUS	current
			::= { hmWanMbus37 13 }

hmWanMbus37VIF04		OBJECT-TYPE
			SYNTAX	INTEGER
			MAX-ACCESS	read-only
			STATUS	current
			::= { hmWanMbus37 14 }

hmWanMbus37Value04		OBJECT-TYPE
			SYNTAX	INTEGER
			MAX-ACCESS	read-only
			STATUS	current
			::= { hmWanMbus37 15 }

hmWanMbus37VIF05		OBJECT-TYPE
			SYNTAX	INTEGER
			MAX-ACCESS	read-only
			STATUS	current
			::= { hmWanMbus37 16 }

hmWanMbus37Value05		OBJECT-TYPE
			SYNTAX	INTEGER
			MAX-ACCESS	read-only
			STATUS	current
			::= { hmWanMbus37 17 }

hmWanMbus37VIF06		OBJECT-TYPE
			SYNTAX	INTEGER
			MAX-ACCESS	read-only
			STATUS	current
			::= { hmWanMbus37 18 }

hmWanMbus37Value06		OBJECT-TYPE
			SYNTAX	INTEGER
			MAX-ACCESS	read-only
			STATUS	current
			::= { hmWanMbus37 19 }

hmWanMbus37VIF07		OBJECT-TYPE
			SYNTAX	INTEGER
			MAX-ACCESS	read-only
			STATUS	current
			::= { hmWanMbus37 20 }

hmWanMbus37Value07		OBJECT-TYPE
			SYNTAX	INTEGER
			MAX-ACCESS	read-only
			STATUS	current
			::= { hmWanMbus37 21 }

hmWanMbus37VIF08		OBJECT-TYPE
			SYNTAX	INTEGER
			MAX-ACCESS	read-only
			STATUS	current
			::= { hmWanMbus37 22 }

hmWanMbus37Value08		OBJECT-TYPE
			SYNTAX	INTEGER
			MAX-ACCESS	read-only
			STATUS	current
			::= { hmWanMbus37 23 }

hmWanMbus37VIF09		OBJECT-TYPE
			SYNTAX	INTEGER
			MAX-ACCESS	read-only
			STATUS	current
			::= { hmWanMbus37 24 }

hmWanMbus37Value09		OBJECT-TYPE
			SYNTAX	INTEGER
			MAX-ACCESS	read-only
			STATUS	current
			::= { hmWanMbus37 25 }

hmWanMbus37VIF0A		OBJECT-TYPE
			SYNTAX	INTEGER
			MAX-ACCESS	read-only
			STATUS	current
			::= { hmWanMbus37 26 }

hmWanMbus37Value0A		OBJECT-TYPE
			SYNTAX	INTEGER
			MAX-ACCESS	read-only
			STATUS	current
			::= { hmWanMbus37 27 }

hmWanMbus37VIF0B		OBJECT-TYPE
			SYNTAX	INTEGER
			MAX-ACCESS	read-only
			STATUS	current
			::= { hmWanMbus37 28 }

hmWanMbus37Value0B		OBJECT-TYPE
			SYNTAX	INTEGER
			MAX-ACCESS	read-only
			STATUS	current
			::= { hmWanMbus37 29 }

hmWanMbus37VIF0C		OBJECT-TYPE
			SYNTAX	INTEGER
			MAX-ACCESS	read-only
			STATUS	current
			::= { hmWanMbus37 30 }

hmWanMbus37Value0C		OBJECT-TYPE
			SYNTAX	INTEGER
			MAX-ACCESS	read-only
			STATUS	current
			::= { hmWanMbus37 31 }

hmWanMbus37VIF0D		OBJECT-TYPE
			SYNTAX	INTEGER
			MAX-ACCESS	read-only
			STATUS	current
			::= { hmWanMbus37 32 }

hmWanMbus37Value0D		OBJECT-TYPE
			SYNTAX	INTEGER
			MAX-ACCESS	read-only
			STATUS	current
			::= { hmWanMbus37 33 }

hmWanMbus37VIF0E		OBJECT-TYPE
			SYNTAX	INTEGER
			MAX-ACCESS	read-only
			STATUS	current
			::= { hmWanMbus37 34 }

hmWanMbus37Value0E		OBJECT-TYPE
			SYNTAX	INTEGER
			MAX-ACCESS	read-only
			STATUS	current
			::= { hmWanMbus37 35 }

hmWanMbus37VIF0F		OBJECT-TYPE
			SYNTAX	INTEGER
			MAX-ACCESS	read-only
			STATUS	current
			::= { hmWanMbus37 36 }

hmWanMbus37Value0F		OBJECT-TYPE
			SYNTAX	INTEGER
			MAX-ACCESS	read-only
			STATUS	current
			::= { hmWanMbus37 37 }

hmWanMbus37VIF10		OBJECT-TYPE
			SYNTAX	INTEGER
			MAX-ACCESS	read-only
			STATUS	current
			::= { hmWanMbus37 38 }

hmWanMbus37Value10		OBJECT-TYPE
			SYNTAX	INTEGER
			MAX-ACCESS	read-only
			STATUS	current
			::= { hmWanMbus37 39 }

hmWanMbus37VIF11		OBJECT-TYPE
			SYNTAX	INTEGER
			MAX-ACCESS	read-only
			STATUS	current
			::= { hmWanMbus37 40 }

hmWanMbus37Value11		OBJECT-TYPE
			SYNTAX	INTEGER
			MAX-ACCESS	read-only
			STATUS	current
			::= { hmWanMbus37 41 }

hmWanMbus37VIF12		OBJECT-TYPE
			SYNTAX	INTEGER
			MAX-ACCESS	read-only
			STATUS	current
			::= { hmWanMbus37 42 }

hmWanMbus37Value12		OBJECT-TYPE
			SYNTAX	INTEGER
			MAX-ACCESS	read-only
			STATUS	current
			::= { hmWanMbus37 43 }

hmWanMbus37VIF13		OBJECT-TYPE
			SYNTAX	INTEGER
			MAX-ACCESS	read-only
			STATUS	current
			::= { hmWanMbus37 44 }

hmWanMbus37Value13		OBJECT-TYPE
			SYNTAX	INTEGER
			MAX-ACCESS	read-only
			STATUS	current
			::= { hmWanMbus37 45 }

hmWanMbus37VIF14		OBJECT-TYPE
			SYNTAX	INTEGER
			MAX-ACCESS	read-only
			STATUS	current
			::= { hmWanMbus37 46 }

hmWanMbus37Value14		OBJECT-TYPE
			SYNTAX	INTEGER
			MAX-ACCESS	read-only
			STATUS	current
			::= { hmWanMbus37 47 }

hmWanMbus37VIF15		OBJECT-TYPE
			SYNTAX	INTEGER
			MAX-ACCESS	read-only
			STATUS	current
			::= { hmWanMbus37 48 }

hmWanMbus37Value15		OBJECT-TYPE
			SYNTAX	INTEGER
			MAX-ACCESS	read-only
			STATUS	current
			::= { hmWanMbus37 49 }

hmWanMbus37VIF16		OBJECT-TYPE
			SYNTAX	INTEGER
			MAX-ACCESS	read-only
			STATUS	current
			::= { hmWanMbus37 50 }

hmWanMbus37Value16		OBJECT-TYPE
			SYNTAX	INTEGER
			MAX-ACCESS	read-only
			STATUS	current
			::= { hmWanMbus37 51 }

hmWanMbus37VIF17		OBJECT-TYPE
			SYNTAX	INTEGER
			MAX-ACCESS	read-only
			STATUS	current
			::= { hmWanMbus37 52 }

hmWanMbus37Value17		OBJECT-TYPE
			SYNTAX	INTEGER
			MAX-ACCESS	read-only
			STATUS	current
			::= { hmWanMbus37 53 }

hmWanMbus37VIF18		OBJECT-TYPE
			SYNTAX	INTEGER
			MAX-ACCESS	read-only
			STATUS	current
			::= { hmWanMbus37 54 }

hmWanMbus37Value18		OBJECT-TYPE
			SYNTAX	INTEGER
			MAX-ACCESS	read-only
			STATUS	current
			::= { hmWanMbus37 55 }

hmWanMbus37VIF19		OBJECT-TYPE
			SYNTAX	INTEGER
			MAX-ACCESS	read-only
			STATUS	current
			::= { hmWanMbus37 56 }

hmWanMbus37Value19		OBJECT-TYPE
			SYNTAX	INTEGER
			MAX-ACCESS	read-only
			STATUS	current
			::= { hmWanMbus37 57 }

hmWanMbus37VIF1A		OBJECT-TYPE
			SYNTAX	INTEGER
			MAX-ACCESS	read-only
			STATUS	current
			::= { hmWanMbus37 58 }

hmWanMbus37Value1A		OBJECT-TYPE
			SYNTAX	INTEGER
			MAX-ACCESS	read-only
			STATUS	current
			::= { hmWanMbus37 59 }

hmWanMbus37VIF1B		OBJECT-TYPE
			SYNTAX	INTEGER
			MAX-ACCESS	read-only
			STATUS	current
			::= { hmWanMbus37 60 }

hmWanMbus37Value1B		OBJECT-TYPE
			SYNTAX	INTEGER
			MAX-ACCESS	read-only
			STATUS	current
			::= { hmWanMbus37 61 }

hmWanMbus37VIF1C		OBJECT-TYPE
			SYNTAX	INTEGER
			MAX-ACCESS	read-only
			STATUS	current
			::= { hmWanMbus37 62 }

hmWanMbus37Value1C		OBJECT-TYPE
			SYNTAX	INTEGER
			MAX-ACCESS	read-only
			STATUS	current
			::= { hmWanMbus37 63 }

hmWanMbus37VIF1D		OBJECT-TYPE
			SYNTAX	INTEGER
			MAX-ACCESS	read-only
			STATUS	current
			::= { hmWanMbus37 64 }

hmWanMbus37Value1D		OBJECT-TYPE
			SYNTAX	INTEGER
			MAX-ACCESS	read-only
			STATUS	current
			::= { hmWanMbus37 65 }

hmWanMbus37VIF1E		OBJECT-TYPE
			SYNTAX	INTEGER
			MAX-ACCESS	read-only
			STATUS	current
			::= { hmWanMbus37 66 }

hmWanMbus37Value1E		OBJECT-TYPE
			SYNTAX	INTEGER
			MAX-ACCESS	read-only
			STATUS	current
			::= { hmWanMbus37 67 }

hmWanMbus37VIF1F		OBJECT-TYPE
			SYNTAX	INTEGER
			MAX-ACCESS	read-only
			STATUS	current
			::= { hmWanMbus37 68 }

hmWanMbus37Value1F		OBJECT-TYPE
			SYNTAX	INTEGER
			MAX-ACCESS	read-only
			STATUS	current
			::= { hmWanMbus37 69 }

hmWanMbus37VIF20		OBJECT-TYPE
			SYNTAX	INTEGER
			MAX-ACCESS	read-only
			STATUS	current
			::= { hmWanMbus37 70 }

hmWanMbus37Value20		OBJECT-TYPE
			SYNTAX	INTEGER
			MAX-ACCESS	read-only
			STATUS	current
			::= { hmWanMbus37 71 }

hmWanMbus37VIF21		OBJECT-TYPE
			SYNTAX	INTEGER
			MAX-ACCESS	read-only
			STATUS	current
			::= { hmWanMbus37 72 }

hmWanMbus37Value21		OBJECT-TYPE
			SYNTAX	INTEGER
			MAX-ACCESS	read-only
			STATUS	current
			::= { hmWanMbus37 73 }

hmWanMbus37VIF22		OBJECT-TYPE
			SYNTAX	INTEGER
			MAX-ACCESS	read-only
			STATUS	current
			::= { hmWanMbus37 74 }

hmWanMbus37Value22		OBJECT-TYPE
			SYNTAX	INTEGER
			MAX-ACCESS	read-only
			STATUS	current
			::= { hmWanMbus37 75 }

hmWanMbus37VIF23		OBJECT-TYPE
			SYNTAX	INTEGER
			MAX-ACCESS	read-only
			STATUS	current
			::= { hmWanMbus37 76 }

hmWanMbus37Value23		OBJECT-TYPE
			SYNTAX	INTEGER
			MAX-ACCESS	read-only
			STATUS	current
			::= { hmWanMbus37 77 }

hmWanMbus37VIF24		OBJECT-TYPE
			SYNTAX	INTEGER
			MAX-ACCESS	read-only
			STATUS	current
			::= { hmWanMbus37 78 }

hmWanMbus37Value24		OBJECT-TYPE
			SYNTAX	INTEGER
			MAX-ACCESS	read-only
			STATUS	current
			::= { hmWanMbus37 79 }

hmWanMbus37VIF25		OBJECT-TYPE
			SYNTAX	INTEGER
			MAX-ACCESS	read-only
			STATUS	current
			::= { hmWanMbus37 80 }

hmWanMbus37Value25		OBJECT-TYPE
			SYNTAX	INTEGER
			MAX-ACCESS	read-only
			STATUS	current
			::= { hmWanMbus37 81 }

hmWanMbus37VIF26		OBJECT-TYPE
			SYNTAX	INTEGER
			MAX-ACCESS	read-only
			STATUS	current
			::= { hmWanMbus37 82 }

hmWanMbus37Value26		OBJECT-TYPE
			SYNTAX	INTEGER
			MAX-ACCESS	read-only
			STATUS	current
			::= { hmWanMbus37 83 }

hmWanMbus37VIF27		OBJECT-TYPE
			SYNTAX	INTEGER
			MAX-ACCESS	read-only
			STATUS	current
			::= { hmWanMbus37 84 }

hmWanMbus37Value27		OBJECT-TYPE
			SYNTAX	INTEGER
			MAX-ACCESS	read-only
			STATUS	current
			::= { hmWanMbus37 85 }

hmWanMbus37VIF28		OBJECT-TYPE
			SYNTAX	INTEGER
			MAX-ACCESS	read-only
			STATUS	current
			::= { hmWanMbus37 86 }

hmWanMbus37Value28		OBJECT-TYPE
			SYNTAX	INTEGER
			MAX-ACCESS	read-only
			STATUS	current
			::= { hmWanMbus37 87 }

hmWanMbus37VIF29		OBJECT-TYPE
			SYNTAX	INTEGER
			MAX-ACCESS	read-only
			STATUS	current
			::= { hmWanMbus37 88 }

hmWanMbus37Value29		OBJECT-TYPE
			SYNTAX	INTEGER
			MAX-ACCESS	read-only
			STATUS	current
			::= { hmWanMbus37 89 }

hmWanMbus37VIF2A		OBJECT-TYPE
			SYNTAX	INTEGER
			MAX-ACCESS	read-only
			STATUS	current
			::= { hmWanMbus37 90 }

hmWanMbus37Value2A		OBJECT-TYPE
			SYNTAX	INTEGER
			MAX-ACCESS	read-only
			STATUS	current
			::= { hmWanMbus37 91 }

hmWanMbus37VIF2B		OBJECT-TYPE
			SYNTAX	INTEGER
			MAX-ACCESS	read-only
			STATUS	current
			::= { hmWanMbus37 92 }

hmWanMbus37Value2B		OBJECT-TYPE
			SYNTAX	INTEGER
			MAX-ACCESS	read-only
			STATUS	current
			::= { hmWanMbus37 93 }

hmWanMbus37VIF2C		OBJECT-TYPE
			SYNTAX	INTEGER
			MAX-ACCESS	read-only
			STATUS	current
			::= { hmWanMbus37 94 }

hmWanMbus37Value2C		OBJECT-TYPE
			SYNTAX	INTEGER
			MAX-ACCESS	read-only
			STATUS	current
			::= { hmWanMbus37 95 }

hmWanMbus37VIF2D		OBJECT-TYPE
			SYNTAX	INTEGER
			MAX-ACCESS	read-only
			STATUS	current
			::= { hmWanMbus37 96 }

hmWanMbus37Value2D		OBJECT-TYPE
			SYNTAX	INTEGER
			MAX-ACCESS	read-only
			STATUS	current
			::= { hmWanMbus37 97 }

hmWanMbus37VIF2E		OBJECT-TYPE
			SYNTAX	INTEGER
			MAX-ACCESS	read-only
			STATUS	current
			::= { hmWanMbus37 98 }

hmWanMbus37Value2E		OBJECT-TYPE
			SYNTAX	INTEGER
			MAX-ACCESS	read-only
			STATUS	current
			::= { hmWanMbus37 99 }

hmWanMbus37VIF2F		OBJECT-TYPE
			SYNTAX	INTEGER
			MAX-ACCESS	read-only
			STATUS	current
			::= { hmWanMbus37 100 }

hmWanMbus37Value2F		OBJECT-TYPE
			SYNTAX	INTEGER
			MAX-ACCESS	read-only
			STATUS	current
			::= { hmWanMbus37 101 }

hmWanMbus38			OBJECT IDENTIFIER ::= { hmWanMbus 56 }

hmWanMbus38IdNumber		OBJECT-TYPE
			SYNTAX	Gauge32
			MAX-ACCESS	read-only
			STATUS	current
			::= { hmWanMbus38 1 }

hmWanMbus38Manufacturer	OBJECT-TYPE
			SYNTAX	Gauge32
			MAX-ACCESS	read-only
			STATUS	current
			::= { hmWanMbus38 2 }

hmWanMbus38Version		OBJECT-TYPE
			SYNTAX	Gauge32
			MAX-ACCESS	read-only
			STATUS	current
			::= { hmWanMbus38 3 }

hmWanMbus38Medium		OBJECT-TYPE
			SYNTAX	Gauge32
			MAX-ACCESS	read-only
			STATUS	current
			::= { hmWanMbus38 4 }

hmWanMbus38Status		OBJECT-TYPE
			SYNTAX	Gauge32
			MAX-ACCESS	read-only
			STATUS	current
			::= { hmWanMbus38 5 }

hmWanMbus38VIF00		OBJECT-TYPE
			SYNTAX	INTEGER
			MAX-ACCESS	read-only
			STATUS	current
			::= { hmWanMbus38 6 }

hmWanMbus38Value00		OBJECT-TYPE
			SYNTAX	INTEGER
			MAX-ACCESS	read-only
			STATUS	current
			::= { hmWanMbus38 7 }

hmWanMbus38VIF01		OBJECT-TYPE
			SYNTAX	INTEGER
			MAX-ACCESS	read-only
			STATUS	current
			::= { hmWanMbus38 8 }

hmWanMbus38Value01		OBJECT-TYPE
			SYNTAX	INTEGER
			MAX-ACCESS	read-only
			STATUS	current
			::= { hmWanMbus38 9 }

hmWanMbus38VIF02		OBJECT-TYPE
			SYNTAX	INTEGER
			MAX-ACCESS	read-only
			STATUS	current
			::= { hmWanMbus38 10 }

hmWanMbus38Value02		OBJECT-TYPE
			SYNTAX	INTEGER
			MAX-ACCESS	read-only
			STATUS	current
			::= { hmWanMbus38 11 }

hmWanMbus38VIF03		OBJECT-TYPE
			SYNTAX	INTEGER
			MAX-ACCESS	read-only
			STATUS	current
			::= { hmWanMbus38 12 }

hmWanMbus38Value03		OBJECT-TYPE
			SYNTAX	INTEGER
			MAX-ACCESS	read-only
			STATUS	current
			::= { hmWanMbus38 13 }

hmWanMbus38VIF04		OBJECT-TYPE
			SYNTAX	INTEGER
			MAX-ACCESS	read-only
			STATUS	current
			::= { hmWanMbus38 14 }

hmWanMbus38Value04		OBJECT-TYPE
			SYNTAX	INTEGER
			MAX-ACCESS	read-only
			STATUS	current
			::= { hmWanMbus38 15 }

hmWanMbus38VIF05		OBJECT-TYPE
			SYNTAX	INTEGER
			MAX-ACCESS	read-only
			STATUS	current
			::= { hmWanMbus38 16 }

hmWanMbus38Value05		OBJECT-TYPE
			SYNTAX	INTEGER
			MAX-ACCESS	read-only
			STATUS	current
			::= { hmWanMbus38 17 }

hmWanMbus38VIF06		OBJECT-TYPE
			SYNTAX	INTEGER
			MAX-ACCESS	read-only
			STATUS	current
			::= { hmWanMbus38 18 }

hmWanMbus38Value06		OBJECT-TYPE
			SYNTAX	INTEGER
			MAX-ACCESS	read-only
			STATUS	current
			::= { hmWanMbus38 19 }

hmWanMbus38VIF07		OBJECT-TYPE
			SYNTAX	INTEGER
			MAX-ACCESS	read-only
			STATUS	current
			::= { hmWanMbus38 20 }

hmWanMbus38Value07		OBJECT-TYPE
			SYNTAX	INTEGER
			MAX-ACCESS	read-only
			STATUS	current
			::= { hmWanMbus38 21 }

hmWanMbus38VIF08		OBJECT-TYPE
			SYNTAX	INTEGER
			MAX-ACCESS	read-only
			STATUS	current
			::= { hmWanMbus38 22 }

hmWanMbus38Value08		OBJECT-TYPE
			SYNTAX	INTEGER
			MAX-ACCESS	read-only
			STATUS	current
			::= { hmWanMbus38 23 }

hmWanMbus38VIF09		OBJECT-TYPE
			SYNTAX	INTEGER
			MAX-ACCESS	read-only
			STATUS	current
			::= { hmWanMbus38 24 }

hmWanMbus38Value09		OBJECT-TYPE
			SYNTAX	INTEGER
			MAX-ACCESS	read-only
			STATUS	current
			::= { hmWanMbus38 25 }

hmWanMbus38VIF0A		OBJECT-TYPE
			SYNTAX	INTEGER
			MAX-ACCESS	read-only
			STATUS	current
			::= { hmWanMbus38 26 }

hmWanMbus38Value0A		OBJECT-TYPE
			SYNTAX	INTEGER
			MAX-ACCESS	read-only
			STATUS	current
			::= { hmWanMbus38 27 }

hmWanMbus38VIF0B		OBJECT-TYPE
			SYNTAX	INTEGER
			MAX-ACCESS	read-only
			STATUS	current
			::= { hmWanMbus38 28 }

hmWanMbus38Value0B		OBJECT-TYPE
			SYNTAX	INTEGER
			MAX-ACCESS	read-only
			STATUS	current
			::= { hmWanMbus38 29 }

hmWanMbus38VIF0C		OBJECT-TYPE
			SYNTAX	INTEGER
			MAX-ACCESS	read-only
			STATUS	current
			::= { hmWanMbus38 30 }

hmWanMbus38Value0C		OBJECT-TYPE
			SYNTAX	INTEGER
			MAX-ACCESS	read-only
			STATUS	current
			::= { hmWanMbus38 31 }

hmWanMbus38VIF0D		OBJECT-TYPE
			SYNTAX	INTEGER
			MAX-ACCESS	read-only
			STATUS	current
			::= { hmWanMbus38 32 }

hmWanMbus38Value0D		OBJECT-TYPE
			SYNTAX	INTEGER
			MAX-ACCESS	read-only
			STATUS	current
			::= { hmWanMbus38 33 }

hmWanMbus38VIF0E		OBJECT-TYPE
			SYNTAX	INTEGER
			MAX-ACCESS	read-only
			STATUS	current
			::= { hmWanMbus38 34 }

hmWanMbus38Value0E		OBJECT-TYPE
			SYNTAX	INTEGER
			MAX-ACCESS	read-only
			STATUS	current
			::= { hmWanMbus38 35 }

hmWanMbus38VIF0F		OBJECT-TYPE
			SYNTAX	INTEGER
			MAX-ACCESS	read-only
			STATUS	current
			::= { hmWanMbus38 36 }

hmWanMbus38Value0F		OBJECT-TYPE
			SYNTAX	INTEGER
			MAX-ACCESS	read-only
			STATUS	current
			::= { hmWanMbus38 37 }

hmWanMbus38VIF10		OBJECT-TYPE
			SYNTAX	INTEGER
			MAX-ACCESS	read-only
			STATUS	current
			::= { hmWanMbus38 38 }

hmWanMbus38Value10		OBJECT-TYPE
			SYNTAX	INTEGER
			MAX-ACCESS	read-only
			STATUS	current
			::= { hmWanMbus38 39 }

hmWanMbus38VIF11		OBJECT-TYPE
			SYNTAX	INTEGER
			MAX-ACCESS	read-only
			STATUS	current
			::= { hmWanMbus38 40 }

hmWanMbus38Value11		OBJECT-TYPE
			SYNTAX	INTEGER
			MAX-ACCESS	read-only
			STATUS	current
			::= { hmWanMbus38 41 }

hmWanMbus38VIF12		OBJECT-TYPE
			SYNTAX	INTEGER
			MAX-ACCESS	read-only
			STATUS	current
			::= { hmWanMbus38 42 }

hmWanMbus38Value12		OBJECT-TYPE
			SYNTAX	INTEGER
			MAX-ACCESS	read-only
			STATUS	current
			::= { hmWanMbus38 43 }

hmWanMbus38VIF13		OBJECT-TYPE
			SYNTAX	INTEGER
			MAX-ACCESS	read-only
			STATUS	current
			::= { hmWanMbus38 44 }

hmWanMbus38Value13		OBJECT-TYPE
			SYNTAX	INTEGER
			MAX-ACCESS	read-only
			STATUS	current
			::= { hmWanMbus38 45 }

hmWanMbus38VIF14		OBJECT-TYPE
			SYNTAX	INTEGER
			MAX-ACCESS	read-only
			STATUS	current
			::= { hmWanMbus38 46 }

hmWanMbus38Value14		OBJECT-TYPE
			SYNTAX	INTEGER
			MAX-ACCESS	read-only
			STATUS	current
			::= { hmWanMbus38 47 }

hmWanMbus38VIF15		OBJECT-TYPE
			SYNTAX	INTEGER
			MAX-ACCESS	read-only
			STATUS	current
			::= { hmWanMbus38 48 }

hmWanMbus38Value15		OBJECT-TYPE
			SYNTAX	INTEGER
			MAX-ACCESS	read-only
			STATUS	current
			::= { hmWanMbus38 49 }

hmWanMbus38VIF16		OBJECT-TYPE
			SYNTAX	INTEGER
			MAX-ACCESS	read-only
			STATUS	current
			::= { hmWanMbus38 50 }

hmWanMbus38Value16		OBJECT-TYPE
			SYNTAX	INTEGER
			MAX-ACCESS	read-only
			STATUS	current
			::= { hmWanMbus38 51 }

hmWanMbus38VIF17		OBJECT-TYPE
			SYNTAX	INTEGER
			MAX-ACCESS	read-only
			STATUS	current
			::= { hmWanMbus38 52 }

hmWanMbus38Value17		OBJECT-TYPE
			SYNTAX	INTEGER
			MAX-ACCESS	read-only
			STATUS	current
			::= { hmWanMbus38 53 }

hmWanMbus38VIF18		OBJECT-TYPE
			SYNTAX	INTEGER
			MAX-ACCESS	read-only
			STATUS	current
			::= { hmWanMbus38 54 }

hmWanMbus38Value18		OBJECT-TYPE
			SYNTAX	INTEGER
			MAX-ACCESS	read-only
			STATUS	current
			::= { hmWanMbus38 55 }

hmWanMbus38VIF19		OBJECT-TYPE
			SYNTAX	INTEGER
			MAX-ACCESS	read-only
			STATUS	current
			::= { hmWanMbus38 56 }

hmWanMbus38Value19		OBJECT-TYPE
			SYNTAX	INTEGER
			MAX-ACCESS	read-only
			STATUS	current
			::= { hmWanMbus38 57 }

hmWanMbus38VIF1A		OBJECT-TYPE
			SYNTAX	INTEGER
			MAX-ACCESS	read-only
			STATUS	current
			::= { hmWanMbus38 58 }

hmWanMbus38Value1A		OBJECT-TYPE
			SYNTAX	INTEGER
			MAX-ACCESS	read-only
			STATUS	current
			::= { hmWanMbus38 59 }

hmWanMbus38VIF1B		OBJECT-TYPE
			SYNTAX	INTEGER
			MAX-ACCESS	read-only
			STATUS	current
			::= { hmWanMbus38 60 }

hmWanMbus38Value1B		OBJECT-TYPE
			SYNTAX	INTEGER
			MAX-ACCESS	read-only
			STATUS	current
			::= { hmWanMbus38 61 }

hmWanMbus38VIF1C		OBJECT-TYPE
			SYNTAX	INTEGER
			MAX-ACCESS	read-only
			STATUS	current
			::= { hmWanMbus38 62 }

hmWanMbus38Value1C		OBJECT-TYPE
			SYNTAX	INTEGER
			MAX-ACCESS	read-only
			STATUS	current
			::= { hmWanMbus38 63 }

hmWanMbus38VIF1D		OBJECT-TYPE
			SYNTAX	INTEGER
			MAX-ACCESS	read-only
			STATUS	current
			::= { hmWanMbus38 64 }

hmWanMbus38Value1D		OBJECT-TYPE
			SYNTAX	INTEGER
			MAX-ACCESS	read-only
			STATUS	current
			::= { hmWanMbus38 65 }

hmWanMbus38VIF1E		OBJECT-TYPE
			SYNTAX	INTEGER
			MAX-ACCESS	read-only
			STATUS	current
			::= { hmWanMbus38 66 }

hmWanMbus38Value1E		OBJECT-TYPE
			SYNTAX	INTEGER
			MAX-ACCESS	read-only
			STATUS	current
			::= { hmWanMbus38 67 }

hmWanMbus38VIF1F		OBJECT-TYPE
			SYNTAX	INTEGER
			MAX-ACCESS	read-only
			STATUS	current
			::= { hmWanMbus38 68 }

hmWanMbus38Value1F		OBJECT-TYPE
			SYNTAX	INTEGER
			MAX-ACCESS	read-only
			STATUS	current
			::= { hmWanMbus38 69 }

hmWanMbus38VIF20		OBJECT-TYPE
			SYNTAX	INTEGER
			MAX-ACCESS	read-only
			STATUS	current
			::= { hmWanMbus38 70 }

hmWanMbus38Value20		OBJECT-TYPE
			SYNTAX	INTEGER
			MAX-ACCESS	read-only
			STATUS	current
			::= { hmWanMbus38 71 }

hmWanMbus38VIF21		OBJECT-TYPE
			SYNTAX	INTEGER
			MAX-ACCESS	read-only
			STATUS	current
			::= { hmWanMbus38 72 }

hmWanMbus38Value21		OBJECT-TYPE
			SYNTAX	INTEGER
			MAX-ACCESS	read-only
			STATUS	current
			::= { hmWanMbus38 73 }

hmWanMbus38VIF22		OBJECT-TYPE
			SYNTAX	INTEGER
			MAX-ACCESS	read-only
			STATUS	current
			::= { hmWanMbus38 74 }

hmWanMbus38Value22		OBJECT-TYPE
			SYNTAX	INTEGER
			MAX-ACCESS	read-only
			STATUS	current
			::= { hmWanMbus38 75 }

hmWanMbus38VIF23		OBJECT-TYPE
			SYNTAX	INTEGER
			MAX-ACCESS	read-only
			STATUS	current
			::= { hmWanMbus38 76 }

hmWanMbus38Value23		OBJECT-TYPE
			SYNTAX	INTEGER
			MAX-ACCESS	read-only
			STATUS	current
			::= { hmWanMbus38 77 }

hmWanMbus38VIF24		OBJECT-TYPE
			SYNTAX	INTEGER
			MAX-ACCESS	read-only
			STATUS	current
			::= { hmWanMbus38 78 }

hmWanMbus38Value24		OBJECT-TYPE
			SYNTAX	INTEGER
			MAX-ACCESS	read-only
			STATUS	current
			::= { hmWanMbus38 79 }

hmWanMbus38VIF25		OBJECT-TYPE
			SYNTAX	INTEGER
			MAX-ACCESS	read-only
			STATUS	current
			::= { hmWanMbus38 80 }

hmWanMbus38Value25		OBJECT-TYPE
			SYNTAX	INTEGER
			MAX-ACCESS	read-only
			STATUS	current
			::= { hmWanMbus38 81 }

hmWanMbus38VIF26		OBJECT-TYPE
			SYNTAX	INTEGER
			MAX-ACCESS	read-only
			STATUS	current
			::= { hmWanMbus38 82 }

hmWanMbus38Value26		OBJECT-TYPE
			SYNTAX	INTEGER
			MAX-ACCESS	read-only
			STATUS	current
			::= { hmWanMbus38 83 }

hmWanMbus38VIF27		OBJECT-TYPE
			SYNTAX	INTEGER
			MAX-ACCESS	read-only
			STATUS	current
			::= { hmWanMbus38 84 }

hmWanMbus38Value27		OBJECT-TYPE
			SYNTAX	INTEGER
			MAX-ACCESS	read-only
			STATUS	current
			::= { hmWanMbus38 85 }

hmWanMbus38VIF28		OBJECT-TYPE
			SYNTAX	INTEGER
			MAX-ACCESS	read-only
			STATUS	current
			::= { hmWanMbus38 86 }

hmWanMbus38Value28		OBJECT-TYPE
			SYNTAX	INTEGER
			MAX-ACCESS	read-only
			STATUS	current
			::= { hmWanMbus38 87 }

hmWanMbus38VIF29		OBJECT-TYPE
			SYNTAX	INTEGER
			MAX-ACCESS	read-only
			STATUS	current
			::= { hmWanMbus38 88 }

hmWanMbus38Value29		OBJECT-TYPE
			SYNTAX	INTEGER
			MAX-ACCESS	read-only
			STATUS	current
			::= { hmWanMbus38 89 }

hmWanMbus38VIF2A		OBJECT-TYPE
			SYNTAX	INTEGER
			MAX-ACCESS	read-only
			STATUS	current
			::= { hmWanMbus38 90 }

hmWanMbus38Value2A		OBJECT-TYPE
			SYNTAX	INTEGER
			MAX-ACCESS	read-only
			STATUS	current
			::= { hmWanMbus38 91 }

hmWanMbus38VIF2B		OBJECT-TYPE
			SYNTAX	INTEGER
			MAX-ACCESS	read-only
			STATUS	current
			::= { hmWanMbus38 92 }

hmWanMbus38Value2B		OBJECT-TYPE
			SYNTAX	INTEGER
			MAX-ACCESS	read-only
			STATUS	current
			::= { hmWanMbus38 93 }

hmWanMbus38VIF2C		OBJECT-TYPE
			SYNTAX	INTEGER
			MAX-ACCESS	read-only
			STATUS	current
			::= { hmWanMbus38 94 }

hmWanMbus38Value2C		OBJECT-TYPE
			SYNTAX	INTEGER
			MAX-ACCESS	read-only
			STATUS	current
			::= { hmWanMbus38 95 }

hmWanMbus38VIF2D		OBJECT-TYPE
			SYNTAX	INTEGER
			MAX-ACCESS	read-only
			STATUS	current
			::= { hmWanMbus38 96 }

hmWanMbus38Value2D		OBJECT-TYPE
			SYNTAX	INTEGER
			MAX-ACCESS	read-only
			STATUS	current
			::= { hmWanMbus38 97 }

hmWanMbus38VIF2E		OBJECT-TYPE
			SYNTAX	INTEGER
			MAX-ACCESS	read-only
			STATUS	current
			::= { hmWanMbus38 98 }

hmWanMbus38Value2E		OBJECT-TYPE
			SYNTAX	INTEGER
			MAX-ACCESS	read-only
			STATUS	current
			::= { hmWanMbus38 99 }

hmWanMbus38VIF2F		OBJECT-TYPE
			SYNTAX	INTEGER
			MAX-ACCESS	read-only
			STATUS	current
			::= { hmWanMbus38 100 }

hmWanMbus38Value2F		OBJECT-TYPE
			SYNTAX	INTEGER
			MAX-ACCESS	read-only
			STATUS	current
			::= { hmWanMbus38 101 }

hmWanMbus39			OBJECT IDENTIFIER ::= { hmWanMbus 57 }

hmWanMbus39IdNumber		OBJECT-TYPE
			SYNTAX	Gauge32
			MAX-ACCESS	read-only
			STATUS	current
			::= { hmWanMbus39 1 }

hmWanMbus39Manufacturer	OBJECT-TYPE
			SYNTAX	Gauge32
			MAX-ACCESS	read-only
			STATUS	current
			::= { hmWanMbus39 2 }

hmWanMbus39Version		OBJECT-TYPE
			SYNTAX	Gauge32
			MAX-ACCESS	read-only
			STATUS	current
			::= { hmWanMbus39 3 }

hmWanMbus39Medium		OBJECT-TYPE
			SYNTAX	Gauge32
			MAX-ACCESS	read-only
			STATUS	current
			::= { hmWanMbus39 4 }

hmWanMbus39Status		OBJECT-TYPE
			SYNTAX	Gauge32
			MAX-ACCESS	read-only
			STATUS	current
			::= { hmWanMbus39 5 }

hmWanMbus39VIF00		OBJECT-TYPE
			SYNTAX	INTEGER
			MAX-ACCESS	read-only
			STATUS	current
			::= { hmWanMbus39 6 }

hmWanMbus39Value00		OBJECT-TYPE
			SYNTAX	INTEGER
			MAX-ACCESS	read-only
			STATUS	current
			::= { hmWanMbus39 7 }

hmWanMbus39VIF01		OBJECT-TYPE
			SYNTAX	INTEGER
			MAX-ACCESS	read-only
			STATUS	current
			::= { hmWanMbus39 8 }

hmWanMbus39Value01		OBJECT-TYPE
			SYNTAX	INTEGER
			MAX-ACCESS	read-only
			STATUS	current
			::= { hmWanMbus39 9 }

hmWanMbus39VIF02		OBJECT-TYPE
			SYNTAX	INTEGER
			MAX-ACCESS	read-only
			STATUS	current
			::= { hmWanMbus39 10 }

hmWanMbus39Value02		OBJECT-TYPE
			SYNTAX	INTEGER
			MAX-ACCESS	read-only
			STATUS	current
			::= { hmWanMbus39 11 }

hmWanMbus39VIF03		OBJECT-TYPE
			SYNTAX	INTEGER
			MAX-ACCESS	read-only
			STATUS	current
			::= { hmWanMbus39 12 }

hmWanMbus39Value03		OBJECT-TYPE
			SYNTAX	INTEGER
			MAX-ACCESS	read-only
			STATUS	current
			::= { hmWanMbus39 13 }

hmWanMbus39VIF04		OBJECT-TYPE
			SYNTAX	INTEGER
			MAX-ACCESS	read-only
			STATUS	current
			::= { hmWanMbus39 14 }

hmWanMbus39Value04		OBJECT-TYPE
			SYNTAX	INTEGER
			MAX-ACCESS	read-only
			STATUS	current
			::= { hmWanMbus39 15 }

hmWanMbus39VIF05		OBJECT-TYPE
			SYNTAX	INTEGER
			MAX-ACCESS	read-only
			STATUS	current
			::= { hmWanMbus39 16 }

hmWanMbus39Value05		OBJECT-TYPE
			SYNTAX	INTEGER
			MAX-ACCESS	read-only
			STATUS	current
			::= { hmWanMbus39 17 }

hmWanMbus39VIF06		OBJECT-TYPE
			SYNTAX	INTEGER
			MAX-ACCESS	read-only
			STATUS	current
			::= { hmWanMbus39 18 }

hmWanMbus39Value06		OBJECT-TYPE
			SYNTAX	INTEGER
			MAX-ACCESS	read-only
			STATUS	current
			::= { hmWanMbus39 19 }

hmWanMbus39VIF07		OBJECT-TYPE
			SYNTAX	INTEGER
			MAX-ACCESS	read-only
			STATUS	current
			::= { hmWanMbus39 20 }

hmWanMbus39Value07		OBJECT-TYPE
			SYNTAX	INTEGER
			MAX-ACCESS	read-only
			STATUS	current
			::= { hmWanMbus39 21 }

hmWanMbus39VIF08		OBJECT-TYPE
			SYNTAX	INTEGER
			MAX-ACCESS	read-only
			STATUS	current
			::= { hmWanMbus39 22 }

hmWanMbus39Value08		OBJECT-TYPE
			SYNTAX	INTEGER
			MAX-ACCESS	read-only
			STATUS	current
			::= { hmWanMbus39 23 }

hmWanMbus39VIF09		OBJECT-TYPE
			SYNTAX	INTEGER
			MAX-ACCESS	read-only
			STATUS	current
			::= { hmWanMbus39 24 }

hmWanMbus39Value09		OBJECT-TYPE
			SYNTAX	INTEGER
			MAX-ACCESS	read-only
			STATUS	current
			::= { hmWanMbus39 25 }

hmWanMbus39VIF0A		OBJECT-TYPE
			SYNTAX	INTEGER
			MAX-ACCESS	read-only
			STATUS	current
			::= { hmWanMbus39 26 }

hmWanMbus39Value0A		OBJECT-TYPE
			SYNTAX	INTEGER
			MAX-ACCESS	read-only
			STATUS	current
			::= { hmWanMbus39 27 }

hmWanMbus39VIF0B		OBJECT-TYPE
			SYNTAX	INTEGER
			MAX-ACCESS	read-only
			STATUS	current
			::= { hmWanMbus39 28 }

hmWanMbus39Value0B		OBJECT-TYPE
			SYNTAX	INTEGER
			MAX-ACCESS	read-only
			STATUS	current
			::= { hmWanMbus39 29 }

hmWanMbus39VIF0C		OBJECT-TYPE
			SYNTAX	INTEGER
			MAX-ACCESS	read-only
			STATUS	current
			::= { hmWanMbus39 30 }

hmWanMbus39Value0C		OBJECT-TYPE
			SYNTAX	INTEGER
			MAX-ACCESS	read-only
			STATUS	current
			::= { hmWanMbus39 31 }

hmWanMbus39VIF0D		OBJECT-TYPE
			SYNTAX	INTEGER
			MAX-ACCESS	read-only
			STATUS	current
			::= { hmWanMbus39 32 }

hmWanMbus39Value0D		OBJECT-TYPE
			SYNTAX	INTEGER
			MAX-ACCESS	read-only
			STATUS	current
			::= { hmWanMbus39 33 }

hmWanMbus39VIF0E		OBJECT-TYPE
			SYNTAX	INTEGER
			MAX-ACCESS	read-only
			STATUS	current
			::= { hmWanMbus39 34 }

hmWanMbus39Value0E		OBJECT-TYPE
			SYNTAX	INTEGER
			MAX-ACCESS	read-only
			STATUS	current
			::= { hmWanMbus39 35 }

hmWanMbus39VIF0F		OBJECT-TYPE
			SYNTAX	INTEGER
			MAX-ACCESS	read-only
			STATUS	current
			::= { hmWanMbus39 36 }

hmWanMbus39Value0F		OBJECT-TYPE
			SYNTAX	INTEGER
			MAX-ACCESS	read-only
			STATUS	current
			::= { hmWanMbus39 37 }

hmWanMbus39VIF10		OBJECT-TYPE
			SYNTAX	INTEGER
			MAX-ACCESS	read-only
			STATUS	current
			::= { hmWanMbus39 38 }

hmWanMbus39Value10		OBJECT-TYPE
			SYNTAX	INTEGER
			MAX-ACCESS	read-only
			STATUS	current
			::= { hmWanMbus39 39 }

hmWanMbus39VIF11		OBJECT-TYPE
			SYNTAX	INTEGER
			MAX-ACCESS	read-only
			STATUS	current
			::= { hmWanMbus39 40 }

hmWanMbus39Value11		OBJECT-TYPE
			SYNTAX	INTEGER
			MAX-ACCESS	read-only
			STATUS	current
			::= { hmWanMbus39 41 }

hmWanMbus39VIF12		OBJECT-TYPE
			SYNTAX	INTEGER
			MAX-ACCESS	read-only
			STATUS	current
			::= { hmWanMbus39 42 }

hmWanMbus39Value12		OBJECT-TYPE
			SYNTAX	INTEGER
			MAX-ACCESS	read-only
			STATUS	current
			::= { hmWanMbus39 43 }

hmWanMbus39VIF13		OBJECT-TYPE
			SYNTAX	INTEGER
			MAX-ACCESS	read-only
			STATUS	current
			::= { hmWanMbus39 44 }

hmWanMbus39Value13		OBJECT-TYPE
			SYNTAX	INTEGER
			MAX-ACCESS	read-only
			STATUS	current
			::= { hmWanMbus39 45 }

hmWanMbus39VIF14		OBJECT-TYPE
			SYNTAX	INTEGER
			MAX-ACCESS	read-only
			STATUS	current
			::= { hmWanMbus39 46 }

hmWanMbus39Value14		OBJECT-TYPE
			SYNTAX	INTEGER
			MAX-ACCESS	read-only
			STATUS	current
			::= { hmWanMbus39 47 }

hmWanMbus39VIF15		OBJECT-TYPE
			SYNTAX	INTEGER
			MAX-ACCESS	read-only
			STATUS	current
			::= { hmWanMbus39 48 }

hmWanMbus39Value15		OBJECT-TYPE
			SYNTAX	INTEGER
			MAX-ACCESS	read-only
			STATUS	current
			::= { hmWanMbus39 49 }

hmWanMbus39VIF16		OBJECT-TYPE
			SYNTAX	INTEGER
			MAX-ACCESS	read-only
			STATUS	current
			::= { hmWanMbus39 50 }

hmWanMbus39Value16		OBJECT-TYPE
			SYNTAX	INTEGER
			MAX-ACCESS	read-only
			STATUS	current
			::= { hmWanMbus39 51 }

hmWanMbus39VIF17		OBJECT-TYPE
			SYNTAX	INTEGER
			MAX-ACCESS	read-only
			STATUS	current
			::= { hmWanMbus39 52 }

hmWanMbus39Value17		OBJECT-TYPE
			SYNTAX	INTEGER
			MAX-ACCESS	read-only
			STATUS	current
			::= { hmWanMbus39 53 }

hmWanMbus39VIF18		OBJECT-TYPE
			SYNTAX	INTEGER
			MAX-ACCESS	read-only
			STATUS	current
			::= { hmWanMbus39 54 }

hmWanMbus39Value18		OBJECT-TYPE
			SYNTAX	INTEGER
			MAX-ACCESS	read-only
			STATUS	current
			::= { hmWanMbus39 55 }

hmWanMbus39VIF19		OBJECT-TYPE
			SYNTAX	INTEGER
			MAX-ACCESS	read-only
			STATUS	current
			::= { hmWanMbus39 56 }

hmWanMbus39Value19		OBJECT-TYPE
			SYNTAX	INTEGER
			MAX-ACCESS	read-only
			STATUS	current
			::= { hmWanMbus39 57 }

hmWanMbus39VIF1A		OBJECT-TYPE
			SYNTAX	INTEGER
			MAX-ACCESS	read-only
			STATUS	current
			::= { hmWanMbus39 58 }

hmWanMbus39Value1A		OBJECT-TYPE
			SYNTAX	INTEGER
			MAX-ACCESS	read-only
			STATUS	current
			::= { hmWanMbus39 59 }

hmWanMbus39VIF1B		OBJECT-TYPE
			SYNTAX	INTEGER
			MAX-ACCESS	read-only
			STATUS	current
			::= { hmWanMbus39 60 }

hmWanMbus39Value1B		OBJECT-TYPE
			SYNTAX	INTEGER
			MAX-ACCESS	read-only
			STATUS	current
			::= { hmWanMbus39 61 }

hmWanMbus39VIF1C		OBJECT-TYPE
			SYNTAX	INTEGER
			MAX-ACCESS	read-only
			STATUS	current
			::= { hmWanMbus39 62 }

hmWanMbus39Value1C		OBJECT-TYPE
			SYNTAX	INTEGER
			MAX-ACCESS	read-only
			STATUS	current
			::= { hmWanMbus39 63 }

hmWanMbus39VIF1D		OBJECT-TYPE
			SYNTAX	INTEGER
			MAX-ACCESS	read-only
			STATUS	current
			::= { hmWanMbus39 64 }

hmWanMbus39Value1D		OBJECT-TYPE
			SYNTAX	INTEGER
			MAX-ACCESS	read-only
			STATUS	current
			::= { hmWanMbus39 65 }

hmWanMbus39VIF1E		OBJECT-TYPE
			SYNTAX	INTEGER
			MAX-ACCESS	read-only
			STATUS	current
			::= { hmWanMbus39 66 }

hmWanMbus39Value1E		OBJECT-TYPE
			SYNTAX	INTEGER
			MAX-ACCESS	read-only
			STATUS	current
			::= { hmWanMbus39 67 }

hmWanMbus39VIF1F		OBJECT-TYPE
			SYNTAX	INTEGER
			MAX-ACCESS	read-only
			STATUS	current
			::= { hmWanMbus39 68 }

hmWanMbus39Value1F		OBJECT-TYPE
			SYNTAX	INTEGER
			MAX-ACCESS	read-only
			STATUS	current
			::= { hmWanMbus39 69 }

hmWanMbus39VIF20		OBJECT-TYPE
			SYNTAX	INTEGER
			MAX-ACCESS	read-only
			STATUS	current
			::= { hmWanMbus39 70 }

hmWanMbus39Value20		OBJECT-TYPE
			SYNTAX	INTEGER
			MAX-ACCESS	read-only
			STATUS	current
			::= { hmWanMbus39 71 }

hmWanMbus39VIF21		OBJECT-TYPE
			SYNTAX	INTEGER
			MAX-ACCESS	read-only
			STATUS	current
			::= { hmWanMbus39 72 }

hmWanMbus39Value21		OBJECT-TYPE
			SYNTAX	INTEGER
			MAX-ACCESS	read-only
			STATUS	current
			::= { hmWanMbus39 73 }

hmWanMbus39VIF22		OBJECT-TYPE
			SYNTAX	INTEGER
			MAX-ACCESS	read-only
			STATUS	current
			::= { hmWanMbus39 74 }

hmWanMbus39Value22		OBJECT-TYPE
			SYNTAX	INTEGER
			MAX-ACCESS	read-only
			STATUS	current
			::= { hmWanMbus39 75 }

hmWanMbus39VIF23		OBJECT-TYPE
			SYNTAX	INTEGER
			MAX-ACCESS	read-only
			STATUS	current
			::= { hmWanMbus39 76 }

hmWanMbus39Value23		OBJECT-TYPE
			SYNTAX	INTEGER
			MAX-ACCESS	read-only
			STATUS	current
			::= { hmWanMbus39 77 }

hmWanMbus39VIF24		OBJECT-TYPE
			SYNTAX	INTEGER
			MAX-ACCESS	read-only
			STATUS	current
			::= { hmWanMbus39 78 }

hmWanMbus39Value24		OBJECT-TYPE
			SYNTAX	INTEGER
			MAX-ACCESS	read-only
			STATUS	current
			::= { hmWanMbus39 79 }

hmWanMbus39VIF25		OBJECT-TYPE
			SYNTAX	INTEGER
			MAX-ACCESS	read-only
			STATUS	current
			::= { hmWanMbus39 80 }

hmWanMbus39Value25		OBJECT-TYPE
			SYNTAX	INTEGER
			MAX-ACCESS	read-only
			STATUS	current
			::= { hmWanMbus39 81 }

hmWanMbus39VIF26		OBJECT-TYPE
			SYNTAX	INTEGER
			MAX-ACCESS	read-only
			STATUS	current
			::= { hmWanMbus39 82 }

hmWanMbus39Value26		OBJECT-TYPE
			SYNTAX	INTEGER
			MAX-ACCESS	read-only
			STATUS	current
			::= { hmWanMbus39 83 }

hmWanMbus39VIF27		OBJECT-TYPE
			SYNTAX	INTEGER
			MAX-ACCESS	read-only
			STATUS	current
			::= { hmWanMbus39 84 }

hmWanMbus39Value27		OBJECT-TYPE
			SYNTAX	INTEGER
			MAX-ACCESS	read-only
			STATUS	current
			::= { hmWanMbus39 85 }

hmWanMbus39VIF28		OBJECT-TYPE
			SYNTAX	INTEGER
			MAX-ACCESS	read-only
			STATUS	current
			::= { hmWanMbus39 86 }

hmWanMbus39Value28		OBJECT-TYPE
			SYNTAX	INTEGER
			MAX-ACCESS	read-only
			STATUS	current
			::= { hmWanMbus39 87 }

hmWanMbus39VIF29		OBJECT-TYPE
			SYNTAX	INTEGER
			MAX-ACCESS	read-only
			STATUS	current
			::= { hmWanMbus39 88 }

hmWanMbus39Value29		OBJECT-TYPE
			SYNTAX	INTEGER
			MAX-ACCESS	read-only
			STATUS	current
			::= { hmWanMbus39 89 }

hmWanMbus39VIF2A		OBJECT-TYPE
			SYNTAX	INTEGER
			MAX-ACCESS	read-only
			STATUS	current
			::= { hmWanMbus39 90 }

hmWanMbus39Value2A		OBJECT-TYPE
			SYNTAX	INTEGER
			MAX-ACCESS	read-only
			STATUS	current
			::= { hmWanMbus39 91 }

hmWanMbus39VIF2B		OBJECT-TYPE
			SYNTAX	INTEGER
			MAX-ACCESS	read-only
			STATUS	current
			::= { hmWanMbus39 92 }

hmWanMbus39Value2B		OBJECT-TYPE
			SYNTAX	INTEGER
			MAX-ACCESS	read-only
			STATUS	current
			::= { hmWanMbus39 93 }

hmWanMbus39VIF2C		OBJECT-TYPE
			SYNTAX	INTEGER
			MAX-ACCESS	read-only
			STATUS	current
			::= { hmWanMbus39 94 }

hmWanMbus39Value2C		OBJECT-TYPE
			SYNTAX	INTEGER
			MAX-ACCESS	read-only
			STATUS	current
			::= { hmWanMbus39 95 }

hmWanMbus39VIF2D		OBJECT-TYPE
			SYNTAX	INTEGER
			MAX-ACCESS	read-only
			STATUS	current
			::= { hmWanMbus39 96 }

hmWanMbus39Value2D		OBJECT-TYPE
			SYNTAX	INTEGER
			MAX-ACCESS	read-only
			STATUS	current
			::= { hmWanMbus39 97 }

hmWanMbus39VIF2E		OBJECT-TYPE
			SYNTAX	INTEGER
			MAX-ACCESS	read-only
			STATUS	current
			::= { hmWanMbus39 98 }

hmWanMbus39Value2E		OBJECT-TYPE
			SYNTAX	INTEGER
			MAX-ACCESS	read-only
			STATUS	current
			::= { hmWanMbus39 99 }

hmWanMbus39VIF2F		OBJECT-TYPE
			SYNTAX	INTEGER
			MAX-ACCESS	read-only
			STATUS	current
			::= { hmWanMbus39 100 }

hmWanMbus39Value2F		OBJECT-TYPE
			SYNTAX	INTEGER
			MAX-ACCESS	read-only
			STATUS	current
			::= { hmWanMbus39 101 }

hmWanMbus3A			OBJECT IDENTIFIER ::= { hmWanMbus 58 }

hmWanMbus3AIdNumber		OBJECT-TYPE
			SYNTAX	Gauge32
			MAX-ACCESS	read-only
			STATUS	current
			::= { hmWanMbus3A 1 }

hmWanMbus3AManufacturer	OBJECT-TYPE
			SYNTAX	Gauge32
			MAX-ACCESS	read-only
			STATUS	current
			::= { hmWanMbus3A 2 }

hmWanMbus3AVersion		OBJECT-TYPE
			SYNTAX	Gauge32
			MAX-ACCESS	read-only
			STATUS	current
			::= { hmWanMbus3A 3 }

hmWanMbus3AMedium		OBJECT-TYPE
			SYNTAX	Gauge32
			MAX-ACCESS	read-only
			STATUS	current
			::= { hmWanMbus3A 4 }

hmWanMbus3AStatus		OBJECT-TYPE
			SYNTAX	Gauge32
			MAX-ACCESS	read-only
			STATUS	current
			::= { hmWanMbus3A 5 }

hmWanMbus3AVIF00		OBJECT-TYPE
			SYNTAX	INTEGER
			MAX-ACCESS	read-only
			STATUS	current
			::= { hmWanMbus3A 6 }

hmWanMbus3AValue00		OBJECT-TYPE
			SYNTAX	INTEGER
			MAX-ACCESS	read-only
			STATUS	current
			::= { hmWanMbus3A 7 }

hmWanMbus3AVIF01		OBJECT-TYPE
			SYNTAX	INTEGER
			MAX-ACCESS	read-only
			STATUS	current
			::= { hmWanMbus3A 8 }

hmWanMbus3AValue01		OBJECT-TYPE
			SYNTAX	INTEGER
			MAX-ACCESS	read-only
			STATUS	current
			::= { hmWanMbus3A 9 }

hmWanMbus3AVIF02		OBJECT-TYPE
			SYNTAX	INTEGER
			MAX-ACCESS	read-only
			STATUS	current
			::= { hmWanMbus3A 10 }

hmWanMbus3AValue02		OBJECT-TYPE
			SYNTAX	INTEGER
			MAX-ACCESS	read-only
			STATUS	current
			::= { hmWanMbus3A 11 }

hmWanMbus3AVIF03		OBJECT-TYPE
			SYNTAX	INTEGER
			MAX-ACCESS	read-only
			STATUS	current
			::= { hmWanMbus3A 12 }

hmWanMbus3AValue03		OBJECT-TYPE
			SYNTAX	INTEGER
			MAX-ACCESS	read-only
			STATUS	current
			::= { hmWanMbus3A 13 }

hmWanMbus3AVIF04		OBJECT-TYPE
			SYNTAX	INTEGER
			MAX-ACCESS	read-only
			STATUS	current
			::= { hmWanMbus3A 14 }

hmWanMbus3AValue04		OBJECT-TYPE
			SYNTAX	INTEGER
			MAX-ACCESS	read-only
			STATUS	current
			::= { hmWanMbus3A 15 }

hmWanMbus3AVIF05		OBJECT-TYPE
			SYNTAX	INTEGER
			MAX-ACCESS	read-only
			STATUS	current
			::= { hmWanMbus3A 16 }

hmWanMbus3AValue05		OBJECT-TYPE
			SYNTAX	INTEGER
			MAX-ACCESS	read-only
			STATUS	current
			::= { hmWanMbus3A 17 }

hmWanMbus3AVIF06		OBJECT-TYPE
			SYNTAX	INTEGER
			MAX-ACCESS	read-only
			STATUS	current
			::= { hmWanMbus3A 18 }

hmWanMbus3AValue06		OBJECT-TYPE
			SYNTAX	INTEGER
			MAX-ACCESS	read-only
			STATUS	current
			::= { hmWanMbus3A 19 }

hmWanMbus3AVIF07		OBJECT-TYPE
			SYNTAX	INTEGER
			MAX-ACCESS	read-only
			STATUS	current
			::= { hmWanMbus3A 20 }

hmWanMbus3AValue07		OBJECT-TYPE
			SYNTAX	INTEGER
			MAX-ACCESS	read-only
			STATUS	current
			::= { hmWanMbus3A 21 }

hmWanMbus3AVIF08		OBJECT-TYPE
			SYNTAX	INTEGER
			MAX-ACCESS	read-only
			STATUS	current
			::= { hmWanMbus3A 22 }

hmWanMbus3AValue08		OBJECT-TYPE
			SYNTAX	INTEGER
			MAX-ACCESS	read-only
			STATUS	current
			::= { hmWanMbus3A 23 }

hmWanMbus3AVIF09		OBJECT-TYPE
			SYNTAX	INTEGER
			MAX-ACCESS	read-only
			STATUS	current
			::= { hmWanMbus3A 24 }

hmWanMbus3AValue09		OBJECT-TYPE
			SYNTAX	INTEGER
			MAX-ACCESS	read-only
			STATUS	current
			::= { hmWanMbus3A 25 }

hmWanMbus3AVIF0A		OBJECT-TYPE
			SYNTAX	INTEGER
			MAX-ACCESS	read-only
			STATUS	current
			::= { hmWanMbus3A 26 }

hmWanMbus3AValue0A		OBJECT-TYPE
			SYNTAX	INTEGER
			MAX-ACCESS	read-only
			STATUS	current
			::= { hmWanMbus3A 27 }

hmWanMbus3AVIF0B		OBJECT-TYPE
			SYNTAX	INTEGER
			MAX-ACCESS	read-only
			STATUS	current
			::= { hmWanMbus3A 28 }

hmWanMbus3AValue0B		OBJECT-TYPE
			SYNTAX	INTEGER
			MAX-ACCESS	read-only
			STATUS	current
			::= { hmWanMbus3A 29 }

hmWanMbus3AVIF0C		OBJECT-TYPE
			SYNTAX	INTEGER
			MAX-ACCESS	read-only
			STATUS	current
			::= { hmWanMbus3A 30 }

hmWanMbus3AValue0C		OBJECT-TYPE
			SYNTAX	INTEGER
			MAX-ACCESS	read-only
			STATUS	current
			::= { hmWanMbus3A 31 }

hmWanMbus3AVIF0D		OBJECT-TYPE
			SYNTAX	INTEGER
			MAX-ACCESS	read-only
			STATUS	current
			::= { hmWanMbus3A 32 }

hmWanMbus3AValue0D		OBJECT-TYPE
			SYNTAX	INTEGER
			MAX-ACCESS	read-only
			STATUS	current
			::= { hmWanMbus3A 33 }

hmWanMbus3AVIF0E		OBJECT-TYPE
			SYNTAX	INTEGER
			MAX-ACCESS	read-only
			STATUS	current
			::= { hmWanMbus3A 34 }

hmWanMbus3AValue0E		OBJECT-TYPE
			SYNTAX	INTEGER
			MAX-ACCESS	read-only
			STATUS	current
			::= { hmWanMbus3A 35 }

hmWanMbus3AVIF0F		OBJECT-TYPE
			SYNTAX	INTEGER
			MAX-ACCESS	read-only
			STATUS	current
			::= { hmWanMbus3A 36 }

hmWanMbus3AValue0F		OBJECT-TYPE
			SYNTAX	INTEGER
			MAX-ACCESS	read-only
			STATUS	current
			::= { hmWanMbus3A 37 }

hmWanMbus3AVIF10		OBJECT-TYPE
			SYNTAX	INTEGER
			MAX-ACCESS	read-only
			STATUS	current
			::= { hmWanMbus3A 38 }

hmWanMbus3AValue10		OBJECT-TYPE
			SYNTAX	INTEGER
			MAX-ACCESS	read-only
			STATUS	current
			::= { hmWanMbus3A 39 }

hmWanMbus3AVIF11		OBJECT-TYPE
			SYNTAX	INTEGER
			MAX-ACCESS	read-only
			STATUS	current
			::= { hmWanMbus3A 40 }

hmWanMbus3AValue11		OBJECT-TYPE
			SYNTAX	INTEGER
			MAX-ACCESS	read-only
			STATUS	current
			::= { hmWanMbus3A 41 }

hmWanMbus3AVIF12		OBJECT-TYPE
			SYNTAX	INTEGER
			MAX-ACCESS	read-only
			STATUS	current
			::= { hmWanMbus3A 42 }

hmWanMbus3AValue12		OBJECT-TYPE
			SYNTAX	INTEGER
			MAX-ACCESS	read-only
			STATUS	current
			::= { hmWanMbus3A 43 }

hmWanMbus3AVIF13		OBJECT-TYPE
			SYNTAX	INTEGER
			MAX-ACCESS	read-only
			STATUS	current
			::= { hmWanMbus3A 44 }

hmWanMbus3AValue13		OBJECT-TYPE
			SYNTAX	INTEGER
			MAX-ACCESS	read-only
			STATUS	current
			::= { hmWanMbus3A 45 }

hmWanMbus3AVIF14		OBJECT-TYPE
			SYNTAX	INTEGER
			MAX-ACCESS	read-only
			STATUS	current
			::= { hmWanMbus3A 46 }

hmWanMbus3AValue14		OBJECT-TYPE
			SYNTAX	INTEGER
			MAX-ACCESS	read-only
			STATUS	current
			::= { hmWanMbus3A 47 }

hmWanMbus3AVIF15		OBJECT-TYPE
			SYNTAX	INTEGER
			MAX-ACCESS	read-only
			STATUS	current
			::= { hmWanMbus3A 48 }

hmWanMbus3AValue15		OBJECT-TYPE
			SYNTAX	INTEGER
			MAX-ACCESS	read-only
			STATUS	current
			::= { hmWanMbus3A 49 }

hmWanMbus3AVIF16		OBJECT-TYPE
			SYNTAX	INTEGER
			MAX-ACCESS	read-only
			STATUS	current
			::= { hmWanMbus3A 50 }

hmWanMbus3AValue16		OBJECT-TYPE
			SYNTAX	INTEGER
			MAX-ACCESS	read-only
			STATUS	current
			::= { hmWanMbus3A 51 }

hmWanMbus3AVIF17		OBJECT-TYPE
			SYNTAX	INTEGER
			MAX-ACCESS	read-only
			STATUS	current
			::= { hmWanMbus3A 52 }

hmWanMbus3AValue17		OBJECT-TYPE
			SYNTAX	INTEGER
			MAX-ACCESS	read-only
			STATUS	current
			::= { hmWanMbus3A 53 }

hmWanMbus3AVIF18		OBJECT-TYPE
			SYNTAX	INTEGER
			MAX-ACCESS	read-only
			STATUS	current
			::= { hmWanMbus3A 54 }

hmWanMbus3AValue18		OBJECT-TYPE
			SYNTAX	INTEGER
			MAX-ACCESS	read-only
			STATUS	current
			::= { hmWanMbus3A 55 }

hmWanMbus3AVIF19		OBJECT-TYPE
			SYNTAX	INTEGER
			MAX-ACCESS	read-only
			STATUS	current
			::= { hmWanMbus3A 56 }

hmWanMbus3AValue19		OBJECT-TYPE
			SYNTAX	INTEGER
			MAX-ACCESS	read-only
			STATUS	current
			::= { hmWanMbus3A 57 }

hmWanMbus3AVIF1A		OBJECT-TYPE
			SYNTAX	INTEGER
			MAX-ACCESS	read-only
			STATUS	current
			::= { hmWanMbus3A 58 }

hmWanMbus3AValue1A		OBJECT-TYPE
			SYNTAX	INTEGER
			MAX-ACCESS	read-only
			STATUS	current
			::= { hmWanMbus3A 59 }

hmWanMbus3AVIF1B		OBJECT-TYPE
			SYNTAX	INTEGER
			MAX-ACCESS	read-only
			STATUS	current
			::= { hmWanMbus3A 60 }

hmWanMbus3AValue1B		OBJECT-TYPE
			SYNTAX	INTEGER
			MAX-ACCESS	read-only
			STATUS	current
			::= { hmWanMbus3A 61 }

hmWanMbus3AVIF1C		OBJECT-TYPE
			SYNTAX	INTEGER
			MAX-ACCESS	read-only
			STATUS	current
			::= { hmWanMbus3A 62 }

hmWanMbus3AValue1C		OBJECT-TYPE
			SYNTAX	INTEGER
			MAX-ACCESS	read-only
			STATUS	current
			::= { hmWanMbus3A 63 }

hmWanMbus3AVIF1D		OBJECT-TYPE
			SYNTAX	INTEGER
			MAX-ACCESS	read-only
			STATUS	current
			::= { hmWanMbus3A 64 }

hmWanMbus3AValue1D		OBJECT-TYPE
			SYNTAX	INTEGER
			MAX-ACCESS	read-only
			STATUS	current
			::= { hmWanMbus3A 65 }

hmWanMbus3AVIF1E		OBJECT-TYPE
			SYNTAX	INTEGER
			MAX-ACCESS	read-only
			STATUS	current
			::= { hmWanMbus3A 66 }

hmWanMbus3AValue1E		OBJECT-TYPE
			SYNTAX	INTEGER
			MAX-ACCESS	read-only
			STATUS	current
			::= { hmWanMbus3A 67 }

hmWanMbus3AVIF1F		OBJECT-TYPE
			SYNTAX	INTEGER
			MAX-ACCESS	read-only
			STATUS	current
			::= { hmWanMbus3A 68 }

hmWanMbus3AValue1F		OBJECT-TYPE
			SYNTAX	INTEGER
			MAX-ACCESS	read-only
			STATUS	current
			::= { hmWanMbus3A 69 }

hmWanMbus3AVIF20		OBJECT-TYPE
			SYNTAX	INTEGER
			MAX-ACCESS	read-only
			STATUS	current
			::= { hmWanMbus3A 70 }

hmWanMbus3AValue20		OBJECT-TYPE
			SYNTAX	INTEGER
			MAX-ACCESS	read-only
			STATUS	current
			::= { hmWanMbus3A 71 }

hmWanMbus3AVIF21		OBJECT-TYPE
			SYNTAX	INTEGER
			MAX-ACCESS	read-only
			STATUS	current
			::= { hmWanMbus3A 72 }

hmWanMbus3AValue21		OBJECT-TYPE
			SYNTAX	INTEGER
			MAX-ACCESS	read-only
			STATUS	current
			::= { hmWanMbus3A 73 }

hmWanMbus3AVIF22		OBJECT-TYPE
			SYNTAX	INTEGER
			MAX-ACCESS	read-only
			STATUS	current
			::= { hmWanMbus3A 74 }

hmWanMbus3AValue22		OBJECT-TYPE
			SYNTAX	INTEGER
			MAX-ACCESS	read-only
			STATUS	current
			::= { hmWanMbus3A 75 }

hmWanMbus3AVIF23		OBJECT-TYPE
			SYNTAX	INTEGER
			MAX-ACCESS	read-only
			STATUS	current
			::= { hmWanMbus3A 76 }

hmWanMbus3AValue23		OBJECT-TYPE
			SYNTAX	INTEGER
			MAX-ACCESS	read-only
			STATUS	current
			::= { hmWanMbus3A 77 }

hmWanMbus3AVIF24		OBJECT-TYPE
			SYNTAX	INTEGER
			MAX-ACCESS	read-only
			STATUS	current
			::= { hmWanMbus3A 78 }

hmWanMbus3AValue24		OBJECT-TYPE
			SYNTAX	INTEGER
			MAX-ACCESS	read-only
			STATUS	current
			::= { hmWanMbus3A 79 }

hmWanMbus3AVIF25		OBJECT-TYPE
			SYNTAX	INTEGER
			MAX-ACCESS	read-only
			STATUS	current
			::= { hmWanMbus3A 80 }

hmWanMbus3AValue25		OBJECT-TYPE
			SYNTAX	INTEGER
			MAX-ACCESS	read-only
			STATUS	current
			::= { hmWanMbus3A 81 }

hmWanMbus3AVIF26		OBJECT-TYPE
			SYNTAX	INTEGER
			MAX-ACCESS	read-only
			STATUS	current
			::= { hmWanMbus3A 82 }

hmWanMbus3AValue26		OBJECT-TYPE
			SYNTAX	INTEGER
			MAX-ACCESS	read-only
			STATUS	current
			::= { hmWanMbus3A 83 }

hmWanMbus3AVIF27		OBJECT-TYPE
			SYNTAX	INTEGER
			MAX-ACCESS	read-only
			STATUS	current
			::= { hmWanMbus3A 84 }

hmWanMbus3AValue27		OBJECT-TYPE
			SYNTAX	INTEGER
			MAX-ACCESS	read-only
			STATUS	current
			::= { hmWanMbus3A 85 }

hmWanMbus3AVIF28		OBJECT-TYPE
			SYNTAX	INTEGER
			MAX-ACCESS	read-only
			STATUS	current
			::= { hmWanMbus3A 86 }

hmWanMbus3AValue28		OBJECT-TYPE
			SYNTAX	INTEGER
			MAX-ACCESS	read-only
			STATUS	current
			::= { hmWanMbus3A 87 }

hmWanMbus3AVIF29		OBJECT-TYPE
			SYNTAX	INTEGER
			MAX-ACCESS	read-only
			STATUS	current
			::= { hmWanMbus3A 88 }

hmWanMbus3AValue29		OBJECT-TYPE
			SYNTAX	INTEGER
			MAX-ACCESS	read-only
			STATUS	current
			::= { hmWanMbus3A 89 }

hmWanMbus3AVIF2A		OBJECT-TYPE
			SYNTAX	INTEGER
			MAX-ACCESS	read-only
			STATUS	current
			::= { hmWanMbus3A 90 }

hmWanMbus3AValue2A		OBJECT-TYPE
			SYNTAX	INTEGER
			MAX-ACCESS	read-only
			STATUS	current
			::= { hmWanMbus3A 91 }

hmWanMbus3AVIF2B		OBJECT-TYPE
			SYNTAX	INTEGER
			MAX-ACCESS	read-only
			STATUS	current
			::= { hmWanMbus3A 92 }

hmWanMbus3AValue2B		OBJECT-TYPE
			SYNTAX	INTEGER
			MAX-ACCESS	read-only
			STATUS	current
			::= { hmWanMbus3A 93 }

hmWanMbus3AVIF2C		OBJECT-TYPE
			SYNTAX	INTEGER
			MAX-ACCESS	read-only
			STATUS	current
			::= { hmWanMbus3A 94 }

hmWanMbus3AValue2C		OBJECT-TYPE
			SYNTAX	INTEGER
			MAX-ACCESS	read-only
			STATUS	current
			::= { hmWanMbus3A 95 }

hmWanMbus3AVIF2D		OBJECT-TYPE
			SYNTAX	INTEGER
			MAX-ACCESS	read-only
			STATUS	current
			::= { hmWanMbus3A 96 }

hmWanMbus3AValue2D		OBJECT-TYPE
			SYNTAX	INTEGER
			MAX-ACCESS	read-only
			STATUS	current
			::= { hmWanMbus3A 97 }

hmWanMbus3AVIF2E		OBJECT-TYPE
			SYNTAX	INTEGER
			MAX-ACCESS	read-only
			STATUS	current
			::= { hmWanMbus3A 98 }

hmWanMbus3AValue2E		OBJECT-TYPE
			SYNTAX	INTEGER
			MAX-ACCESS	read-only
			STATUS	current
			::= { hmWanMbus3A 99 }

hmWanMbus3AVIF2F		OBJECT-TYPE
			SYNTAX	INTEGER
			MAX-ACCESS	read-only
			STATUS	current
			::= { hmWanMbus3A 100 }

hmWanMbus3AValue2F		OBJECT-TYPE
			SYNTAX	INTEGER
			MAX-ACCESS	read-only
			STATUS	current
			::= { hmWanMbus3A 101 }

hmWanMbus3B			OBJECT IDENTIFIER ::= { hmWanMbus 59 }

hmWanMbus3BIdNumber		OBJECT-TYPE
			SYNTAX	Gauge32
			MAX-ACCESS	read-only
			STATUS	current
			::= { hmWanMbus3B 1 }

hmWanMbus3BManufacturer	OBJECT-TYPE
			SYNTAX	Gauge32
			MAX-ACCESS	read-only
			STATUS	current
			::= { hmWanMbus3B 2 }

hmWanMbus3BVersion		OBJECT-TYPE
			SYNTAX	Gauge32
			MAX-ACCESS	read-only
			STATUS	current
			::= { hmWanMbus3B 3 }

hmWanMbus3BMedium		OBJECT-TYPE
			SYNTAX	Gauge32
			MAX-ACCESS	read-only
			STATUS	current
			::= { hmWanMbus3B 4 }

hmWanMbus3BStatus		OBJECT-TYPE
			SYNTAX	Gauge32
			MAX-ACCESS	read-only
			STATUS	current
			::= { hmWanMbus3B 5 }

hmWanMbus3BVIF00		OBJECT-TYPE
			SYNTAX	INTEGER
			MAX-ACCESS	read-only
			STATUS	current
			::= { hmWanMbus3B 6 }

hmWanMbus3BValue00		OBJECT-TYPE
			SYNTAX	INTEGER
			MAX-ACCESS	read-only
			STATUS	current
			::= { hmWanMbus3B 7 }

hmWanMbus3BVIF01		OBJECT-TYPE
			SYNTAX	INTEGER
			MAX-ACCESS	read-only
			STATUS	current
			::= { hmWanMbus3B 8 }

hmWanMbus3BValue01		OBJECT-TYPE
			SYNTAX	INTEGER
			MAX-ACCESS	read-only
			STATUS	current
			::= { hmWanMbus3B 9 }

hmWanMbus3BVIF02		OBJECT-TYPE
			SYNTAX	INTEGER
			MAX-ACCESS	read-only
			STATUS	current
			::= { hmWanMbus3B 10 }

hmWanMbus3BValue02		OBJECT-TYPE
			SYNTAX	INTEGER
			MAX-ACCESS	read-only
			STATUS	current
			::= { hmWanMbus3B 11 }

hmWanMbus3BVIF03		OBJECT-TYPE
			SYNTAX	INTEGER
			MAX-ACCESS	read-only
			STATUS	current
			::= { hmWanMbus3B 12 }

hmWanMbus3BValue03		OBJECT-TYPE
			SYNTAX	INTEGER
			MAX-ACCESS	read-only
			STATUS	current
			::= { hmWanMbus3B 13 }

hmWanMbus3BVIF04		OBJECT-TYPE
			SYNTAX	INTEGER
			MAX-ACCESS	read-only
			STATUS	current
			::= { hmWanMbus3B 14 }

hmWanMbus3BValue04		OBJECT-TYPE
			SYNTAX	INTEGER
			MAX-ACCESS	read-only
			STATUS	current
			::= { hmWanMbus3B 15 }

hmWanMbus3BVIF05		OBJECT-TYPE
			SYNTAX	INTEGER
			MAX-ACCESS	read-only
			STATUS	current
			::= { hmWanMbus3B 16 }

hmWanMbus3BValue05		OBJECT-TYPE
			SYNTAX	INTEGER
			MAX-ACCESS	read-only
			STATUS	current
			::= { hmWanMbus3B 17 }

hmWanMbus3BVIF06		OBJECT-TYPE
			SYNTAX	INTEGER
			MAX-ACCESS	read-only
			STATUS	current
			::= { hmWanMbus3B 18 }

hmWanMbus3BValue06		OBJECT-TYPE
			SYNTAX	INTEGER
			MAX-ACCESS	read-only
			STATUS	current
			::= { hmWanMbus3B 19 }

hmWanMbus3BVIF07		OBJECT-TYPE
			SYNTAX	INTEGER
			MAX-ACCESS	read-only
			STATUS	current
			::= { hmWanMbus3B 20 }

hmWanMbus3BValue07		OBJECT-TYPE
			SYNTAX	INTEGER
			MAX-ACCESS	read-only
			STATUS	current
			::= { hmWanMbus3B 21 }

hmWanMbus3BVIF08		OBJECT-TYPE
			SYNTAX	INTEGER
			MAX-ACCESS	read-only
			STATUS	current
			::= { hmWanMbus3B 22 }

hmWanMbus3BValue08		OBJECT-TYPE
			SYNTAX	INTEGER
			MAX-ACCESS	read-only
			STATUS	current
			::= { hmWanMbus3B 23 }

hmWanMbus3BVIF09		OBJECT-TYPE
			SYNTAX	INTEGER
			MAX-ACCESS	read-only
			STATUS	current
			::= { hmWanMbus3B 24 }

hmWanMbus3BValue09		OBJECT-TYPE
			SYNTAX	INTEGER
			MAX-ACCESS	read-only
			STATUS	current
			::= { hmWanMbus3B 25 }

hmWanMbus3BVIF0A		OBJECT-TYPE
			SYNTAX	INTEGER
			MAX-ACCESS	read-only
			STATUS	current
			::= { hmWanMbus3B 26 }

hmWanMbus3BValue0A		OBJECT-TYPE
			SYNTAX	INTEGER
			MAX-ACCESS	read-only
			STATUS	current
			::= { hmWanMbus3B 27 }

hmWanMbus3BVIF0B		OBJECT-TYPE
			SYNTAX	INTEGER
			MAX-ACCESS	read-only
			STATUS	current
			::= { hmWanMbus3B 28 }

hmWanMbus3BValue0B		OBJECT-TYPE
			SYNTAX	INTEGER
			MAX-ACCESS	read-only
			STATUS	current
			::= { hmWanMbus3B 29 }

hmWanMbus3BVIF0C		OBJECT-TYPE
			SYNTAX	INTEGER
			MAX-ACCESS	read-only
			STATUS	current
			::= { hmWanMbus3B 30 }

hmWanMbus3BValue0C		OBJECT-TYPE
			SYNTAX	INTEGER
			MAX-ACCESS	read-only
			STATUS	current
			::= { hmWanMbus3B 31 }

hmWanMbus3BVIF0D		OBJECT-TYPE
			SYNTAX	INTEGER
			MAX-ACCESS	read-only
			STATUS	current
			::= { hmWanMbus3B 32 }

hmWanMbus3BValue0D		OBJECT-TYPE
			SYNTAX	INTEGER
			MAX-ACCESS	read-only
			STATUS	current
			::= { hmWanMbus3B 33 }

hmWanMbus3BVIF0E		OBJECT-TYPE
			SYNTAX	INTEGER
			MAX-ACCESS	read-only
			STATUS	current
			::= { hmWanMbus3B 34 }

hmWanMbus3BValue0E		OBJECT-TYPE
			SYNTAX	INTEGER
			MAX-ACCESS	read-only
			STATUS	current
			::= { hmWanMbus3B 35 }

hmWanMbus3BVIF0F		OBJECT-TYPE
			SYNTAX	INTEGER
			MAX-ACCESS	read-only
			STATUS	current
			::= { hmWanMbus3B 36 }

hmWanMbus3BValue0F		OBJECT-TYPE
			SYNTAX	INTEGER
			MAX-ACCESS	read-only
			STATUS	current
			::= { hmWanMbus3B 37 }

hmWanMbus3BVIF10		OBJECT-TYPE
			SYNTAX	INTEGER
			MAX-ACCESS	read-only
			STATUS	current
			::= { hmWanMbus3B 38 }

hmWanMbus3BValue10		OBJECT-TYPE
			SYNTAX	INTEGER
			MAX-ACCESS	read-only
			STATUS	current
			::= { hmWanMbus3B 39 }

hmWanMbus3BVIF11		OBJECT-TYPE
			SYNTAX	INTEGER
			MAX-ACCESS	read-only
			STATUS	current
			::= { hmWanMbus3B 40 }

hmWanMbus3BValue11		OBJECT-TYPE
			SYNTAX	INTEGER
			MAX-ACCESS	read-only
			STATUS	current
			::= { hmWanMbus3B 41 }

hmWanMbus3BVIF12		OBJECT-TYPE
			SYNTAX	INTEGER
			MAX-ACCESS	read-only
			STATUS	current
			::= { hmWanMbus3B 42 }

hmWanMbus3BValue12		OBJECT-TYPE
			SYNTAX	INTEGER
			MAX-ACCESS	read-only
			STATUS	current
			::= { hmWanMbus3B 43 }

hmWanMbus3BVIF13		OBJECT-TYPE
			SYNTAX	INTEGER
			MAX-ACCESS	read-only
			STATUS	current
			::= { hmWanMbus3B 44 }

hmWanMbus3BValue13		OBJECT-TYPE
			SYNTAX	INTEGER
			MAX-ACCESS	read-only
			STATUS	current
			::= { hmWanMbus3B 45 }

hmWanMbus3BVIF14		OBJECT-TYPE
			SYNTAX	INTEGER
			MAX-ACCESS	read-only
			STATUS	current
			::= { hmWanMbus3B 46 }

hmWanMbus3BValue14		OBJECT-TYPE
			SYNTAX	INTEGER
			MAX-ACCESS	read-only
			STATUS	current
			::= { hmWanMbus3B 47 }

hmWanMbus3BVIF15		OBJECT-TYPE
			SYNTAX	INTEGER
			MAX-ACCESS	read-only
			STATUS	current
			::= { hmWanMbus3B 48 }

hmWanMbus3BValue15		OBJECT-TYPE
			SYNTAX	INTEGER
			MAX-ACCESS	read-only
			STATUS	current
			::= { hmWanMbus3B 49 }

hmWanMbus3BVIF16		OBJECT-TYPE
			SYNTAX	INTEGER
			MAX-ACCESS	read-only
			STATUS	current
			::= { hmWanMbus3B 50 }

hmWanMbus3BValue16		OBJECT-TYPE
			SYNTAX	INTEGER
			MAX-ACCESS	read-only
			STATUS	current
			::= { hmWanMbus3B 51 }

hmWanMbus3BVIF17		OBJECT-TYPE
			SYNTAX	INTEGER
			MAX-ACCESS	read-only
			STATUS	current
			::= { hmWanMbus3B 52 }

hmWanMbus3BValue17		OBJECT-TYPE
			SYNTAX	INTEGER
			MAX-ACCESS	read-only
			STATUS	current
			::= { hmWanMbus3B 53 }

hmWanMbus3BVIF18		OBJECT-TYPE
			SYNTAX	INTEGER
			MAX-ACCESS	read-only
			STATUS	current
			::= { hmWanMbus3B 54 }

hmWanMbus3BValue18		OBJECT-TYPE
			SYNTAX	INTEGER
			MAX-ACCESS	read-only
			STATUS	current
			::= { hmWanMbus3B 55 }

hmWanMbus3BVIF19		OBJECT-TYPE
			SYNTAX	INTEGER
			MAX-ACCESS	read-only
			STATUS	current
			::= { hmWanMbus3B 56 }

hmWanMbus3BValue19		OBJECT-TYPE
			SYNTAX	INTEGER
			MAX-ACCESS	read-only
			STATUS	current
			::= { hmWanMbus3B 57 }

hmWanMbus3BVIF1A		OBJECT-TYPE
			SYNTAX	INTEGER
			MAX-ACCESS	read-only
			STATUS	current
			::= { hmWanMbus3B 58 }

hmWanMbus3BValue1A		OBJECT-TYPE
			SYNTAX	INTEGER
			MAX-ACCESS	read-only
			STATUS	current
			::= { hmWanMbus3B 59 }

hmWanMbus3BVIF1B		OBJECT-TYPE
			SYNTAX	INTEGER
			MAX-ACCESS	read-only
			STATUS	current
			::= { hmWanMbus3B 60 }

hmWanMbus3BValue1B		OBJECT-TYPE
			SYNTAX	INTEGER
			MAX-ACCESS	read-only
			STATUS	current
			::= { hmWanMbus3B 61 }

hmWanMbus3BVIF1C		OBJECT-TYPE
			SYNTAX	INTEGER
			MAX-ACCESS	read-only
			STATUS	current
			::= { hmWanMbus3B 62 }

hmWanMbus3BValue1C		OBJECT-TYPE
			SYNTAX	INTEGER
			MAX-ACCESS	read-only
			STATUS	current
			::= { hmWanMbus3B 63 }

hmWanMbus3BVIF1D		OBJECT-TYPE
			SYNTAX	INTEGER
			MAX-ACCESS	read-only
			STATUS	current
			::= { hmWanMbus3B 64 }

hmWanMbus3BValue1D		OBJECT-TYPE
			SYNTAX	INTEGER
			MAX-ACCESS	read-only
			STATUS	current
			::= { hmWanMbus3B 65 }

hmWanMbus3BVIF1E		OBJECT-TYPE
			SYNTAX	INTEGER
			MAX-ACCESS	read-only
			STATUS	current
			::= { hmWanMbus3B 66 }

hmWanMbus3BValue1E		OBJECT-TYPE
			SYNTAX	INTEGER
			MAX-ACCESS	read-only
			STATUS	current
			::= { hmWanMbus3B 67 }

hmWanMbus3BVIF1F		OBJECT-TYPE
			SYNTAX	INTEGER
			MAX-ACCESS	read-only
			STATUS	current
			::= { hmWanMbus3B 68 }

hmWanMbus3BValue1F		OBJECT-TYPE
			SYNTAX	INTEGER
			MAX-ACCESS	read-only
			STATUS	current
			::= { hmWanMbus3B 69 }

hmWanMbus3BVIF20		OBJECT-TYPE
			SYNTAX	INTEGER
			MAX-ACCESS	read-only
			STATUS	current
			::= { hmWanMbus3B 70 }

hmWanMbus3BValue20		OBJECT-TYPE
			SYNTAX	INTEGER
			MAX-ACCESS	read-only
			STATUS	current
			::= { hmWanMbus3B 71 }

hmWanMbus3BVIF21		OBJECT-TYPE
			SYNTAX	INTEGER
			MAX-ACCESS	read-only
			STATUS	current
			::= { hmWanMbus3B 72 }

hmWanMbus3BValue21		OBJECT-TYPE
			SYNTAX	INTEGER
			MAX-ACCESS	read-only
			STATUS	current
			::= { hmWanMbus3B 73 }

hmWanMbus3BVIF22		OBJECT-TYPE
			SYNTAX	INTEGER
			MAX-ACCESS	read-only
			STATUS	current
			::= { hmWanMbus3B 74 }

hmWanMbus3BValue22		OBJECT-TYPE
			SYNTAX	INTEGER
			MAX-ACCESS	read-only
			STATUS	current
			::= { hmWanMbus3B 75 }

hmWanMbus3BVIF23		OBJECT-TYPE
			SYNTAX	INTEGER
			MAX-ACCESS	read-only
			STATUS	current
			::= { hmWanMbus3B 76 }

hmWanMbus3BValue23		OBJECT-TYPE
			SYNTAX	INTEGER
			MAX-ACCESS	read-only
			STATUS	current
			::= { hmWanMbus3B 77 }

hmWanMbus3BVIF24		OBJECT-TYPE
			SYNTAX	INTEGER
			MAX-ACCESS	read-only
			STATUS	current
			::= { hmWanMbus3B 78 }

hmWanMbus3BValue24		OBJECT-TYPE
			SYNTAX	INTEGER
			MAX-ACCESS	read-only
			STATUS	current
			::= { hmWanMbus3B 79 }

hmWanMbus3BVIF25		OBJECT-TYPE
			SYNTAX	INTEGER
			MAX-ACCESS	read-only
			STATUS	current
			::= { hmWanMbus3B 80 }

hmWanMbus3BValue25		OBJECT-TYPE
			SYNTAX	INTEGER
			MAX-ACCESS	read-only
			STATUS	current
			::= { hmWanMbus3B 81 }

hmWanMbus3BVIF26		OBJECT-TYPE
			SYNTAX	INTEGER
			MAX-ACCESS	read-only
			STATUS	current
			::= { hmWanMbus3B 82 }

hmWanMbus3BValue26		OBJECT-TYPE
			SYNTAX	INTEGER
			MAX-ACCESS	read-only
			STATUS	current
			::= { hmWanMbus3B 83 }

hmWanMbus3BVIF27		OBJECT-TYPE
			SYNTAX	INTEGER
			MAX-ACCESS	read-only
			STATUS	current
			::= { hmWanMbus3B 84 }

hmWanMbus3BValue27		OBJECT-TYPE
			SYNTAX	INTEGER
			MAX-ACCESS	read-only
			STATUS	current
			::= { hmWanMbus3B 85 }

hmWanMbus3BVIF28		OBJECT-TYPE
			SYNTAX	INTEGER
			MAX-ACCESS	read-only
			STATUS	current
			::= { hmWanMbus3B 86 }

hmWanMbus3BValue28		OBJECT-TYPE
			SYNTAX	INTEGER
			MAX-ACCESS	read-only
			STATUS	current
			::= { hmWanMbus3B 87 }

hmWanMbus3BVIF29		OBJECT-TYPE
			SYNTAX	INTEGER
			MAX-ACCESS	read-only
			STATUS	current
			::= { hmWanMbus3B 88 }

hmWanMbus3BValue29		OBJECT-TYPE
			SYNTAX	INTEGER
			MAX-ACCESS	read-only
			STATUS	current
			::= { hmWanMbus3B 89 }

hmWanMbus3BVIF2A		OBJECT-TYPE
			SYNTAX	INTEGER
			MAX-ACCESS	read-only
			STATUS	current
			::= { hmWanMbus3B 90 }

hmWanMbus3BValue2A		OBJECT-TYPE
			SYNTAX	INTEGER
			MAX-ACCESS	read-only
			STATUS	current
			::= { hmWanMbus3B 91 }

hmWanMbus3BVIF2B		OBJECT-TYPE
			SYNTAX	INTEGER
			MAX-ACCESS	read-only
			STATUS	current
			::= { hmWanMbus3B 92 }

hmWanMbus3BValue2B		OBJECT-TYPE
			SYNTAX	INTEGER
			MAX-ACCESS	read-only
			STATUS	current
			::= { hmWanMbus3B 93 }

hmWanMbus3BVIF2C		OBJECT-TYPE
			SYNTAX	INTEGER
			MAX-ACCESS	read-only
			STATUS	current
			::= { hmWanMbus3B 94 }

hmWanMbus3BValue2C		OBJECT-TYPE
			SYNTAX	INTEGER
			MAX-ACCESS	read-only
			STATUS	current
			::= { hmWanMbus3B 95 }

hmWanMbus3BVIF2D		OBJECT-TYPE
			SYNTAX	INTEGER
			MAX-ACCESS	read-only
			STATUS	current
			::= { hmWanMbus3B 96 }

hmWanMbus3BValue2D		OBJECT-TYPE
			SYNTAX	INTEGER
			MAX-ACCESS	read-only
			STATUS	current
			::= { hmWanMbus3B 97 }

hmWanMbus3BVIF2E		OBJECT-TYPE
			SYNTAX	INTEGER
			MAX-ACCESS	read-only
			STATUS	current
			::= { hmWanMbus3B 98 }

hmWanMbus3BValue2E		OBJECT-TYPE
			SYNTAX	INTEGER
			MAX-ACCESS	read-only
			STATUS	current
			::= { hmWanMbus3B 99 }

hmWanMbus3BVIF2F		OBJECT-TYPE
			SYNTAX	INTEGER
			MAX-ACCESS	read-only
			STATUS	current
			::= { hmWanMbus3B 100 }

hmWanMbus3BValue2F		OBJECT-TYPE
			SYNTAX	INTEGER
			MAX-ACCESS	read-only
			STATUS	current
			::= { hmWanMbus3B 101 }

hmWanMbus3C			OBJECT IDENTIFIER ::= { hmWanMbus 60 }

hmWanMbus3CIdNumber		OBJECT-TYPE
			SYNTAX	Gauge32
			MAX-ACCESS	read-only
			STATUS	current
			::= { hmWanMbus3C 1 }

hmWanMbus3CManufacturer	OBJECT-TYPE
			SYNTAX	Gauge32
			MAX-ACCESS	read-only
			STATUS	current
			::= { hmWanMbus3C 2 }

hmWanMbus3CVersion		OBJECT-TYPE
			SYNTAX	Gauge32
			MAX-ACCESS	read-only
			STATUS	current
			::= { hmWanMbus3C 3 }

hmWanMbus3CMedium		OBJECT-TYPE
			SYNTAX	Gauge32
			MAX-ACCESS	read-only
			STATUS	current
			::= { hmWanMbus3C 4 }

hmWanMbus3CStatus		OBJECT-TYPE
			SYNTAX	Gauge32
			MAX-ACCESS	read-only
			STATUS	current
			::= { hmWanMbus3C 5 }

hmWanMbus3CVIF00		OBJECT-TYPE
			SYNTAX	INTEGER
			MAX-ACCESS	read-only
			STATUS	current
			::= { hmWanMbus3C 6 }

hmWanMbus3CValue00		OBJECT-TYPE
			SYNTAX	INTEGER
			MAX-ACCESS	read-only
			STATUS	current
			::= { hmWanMbus3C 7 }

hmWanMbus3CVIF01		OBJECT-TYPE
			SYNTAX	INTEGER
			MAX-ACCESS	read-only
			STATUS	current
			::= { hmWanMbus3C 8 }

hmWanMbus3CValue01		OBJECT-TYPE
			SYNTAX	INTEGER
			MAX-ACCESS	read-only
			STATUS	current
			::= { hmWanMbus3C 9 }

hmWanMbus3CVIF02		OBJECT-TYPE
			SYNTAX	INTEGER
			MAX-ACCESS	read-only
			STATUS	current
			::= { hmWanMbus3C 10 }

hmWanMbus3CValue02		OBJECT-TYPE
			SYNTAX	INTEGER
			MAX-ACCESS	read-only
			STATUS	current
			::= { hmWanMbus3C 11 }

hmWanMbus3CVIF03		OBJECT-TYPE
			SYNTAX	INTEGER
			MAX-ACCESS	read-only
			STATUS	current
			::= { hmWanMbus3C 12 }

hmWanMbus3CValue03		OBJECT-TYPE
			SYNTAX	INTEGER
			MAX-ACCESS	read-only
			STATUS	current
			::= { hmWanMbus3C 13 }

hmWanMbus3CVIF04		OBJECT-TYPE
			SYNTAX	INTEGER
			MAX-ACCESS	read-only
			STATUS	current
			::= { hmWanMbus3C 14 }

hmWanMbus3CValue04		OBJECT-TYPE
			SYNTAX	INTEGER
			MAX-ACCESS	read-only
			STATUS	current
			::= { hmWanMbus3C 15 }

hmWanMbus3CVIF05		OBJECT-TYPE
			SYNTAX	INTEGER
			MAX-ACCESS	read-only
			STATUS	current
			::= { hmWanMbus3C 16 }

hmWanMbus3CValue05		OBJECT-TYPE
			SYNTAX	INTEGER
			MAX-ACCESS	read-only
			STATUS	current
			::= { hmWanMbus3C 17 }

hmWanMbus3CVIF06		OBJECT-TYPE
			SYNTAX	INTEGER
			MAX-ACCESS	read-only
			STATUS	current
			::= { hmWanMbus3C 18 }

hmWanMbus3CValue06		OBJECT-TYPE
			SYNTAX	INTEGER
			MAX-ACCESS	read-only
			STATUS	current
			::= { hmWanMbus3C 19 }

hmWanMbus3CVIF07		OBJECT-TYPE
			SYNTAX	INTEGER
			MAX-ACCESS	read-only
			STATUS	current
			::= { hmWanMbus3C 20 }

hmWanMbus3CValue07		OBJECT-TYPE
			SYNTAX	INTEGER
			MAX-ACCESS	read-only
			STATUS	current
			::= { hmWanMbus3C 21 }

hmWanMbus3CVIF08		OBJECT-TYPE
			SYNTAX	INTEGER
			MAX-ACCESS	read-only
			STATUS	current
			::= { hmWanMbus3C 22 }

hmWanMbus3CValue08		OBJECT-TYPE
			SYNTAX	INTEGER
			MAX-ACCESS	read-only
			STATUS	current
			::= { hmWanMbus3C 23 }

hmWanMbus3CVIF09		OBJECT-TYPE
			SYNTAX	INTEGER
			MAX-ACCESS	read-only
			STATUS	current
			::= { hmWanMbus3C 24 }

hmWanMbus3CValue09		OBJECT-TYPE
			SYNTAX	INTEGER
			MAX-ACCESS	read-only
			STATUS	current
			::= { hmWanMbus3C 25 }

hmWanMbus3CVIF0A		OBJECT-TYPE
			SYNTAX	INTEGER
			MAX-ACCESS	read-only
			STATUS	current
			::= { hmWanMbus3C 26 }

hmWanMbus3CValue0A		OBJECT-TYPE
			SYNTAX	INTEGER
			MAX-ACCESS	read-only
			STATUS	current
			::= { hmWanMbus3C 27 }

hmWanMbus3CVIF0B		OBJECT-TYPE
			SYNTAX	INTEGER
			MAX-ACCESS	read-only
			STATUS	current
			::= { hmWanMbus3C 28 }

hmWanMbus3CValue0B		OBJECT-TYPE
			SYNTAX	INTEGER
			MAX-ACCESS	read-only
			STATUS	current
			::= { hmWanMbus3C 29 }

hmWanMbus3CVIF0C		OBJECT-TYPE
			SYNTAX	INTEGER
			MAX-ACCESS	read-only
			STATUS	current
			::= { hmWanMbus3C 30 }

hmWanMbus3CValue0C		OBJECT-TYPE
			SYNTAX	INTEGER
			MAX-ACCESS	read-only
			STATUS	current
			::= { hmWanMbus3C 31 }

hmWanMbus3CVIF0D		OBJECT-TYPE
			SYNTAX	INTEGER
			MAX-ACCESS	read-only
			STATUS	current
			::= { hmWanMbus3C 32 }

hmWanMbus3CValue0D		OBJECT-TYPE
			SYNTAX	INTEGER
			MAX-ACCESS	read-only
			STATUS	current
			::= { hmWanMbus3C 33 }

hmWanMbus3CVIF0E		OBJECT-TYPE
			SYNTAX	INTEGER
			MAX-ACCESS	read-only
			STATUS	current
			::= { hmWanMbus3C 34 }

hmWanMbus3CValue0E		OBJECT-TYPE
			SYNTAX	INTEGER
			MAX-ACCESS	read-only
			STATUS	current
			::= { hmWanMbus3C 35 }

hmWanMbus3CVIF0F		OBJECT-TYPE
			SYNTAX	INTEGER
			MAX-ACCESS	read-only
			STATUS	current
			::= { hmWanMbus3C 36 }

hmWanMbus3CValue0F		OBJECT-TYPE
			SYNTAX	INTEGER
			MAX-ACCESS	read-only
			STATUS	current
			::= { hmWanMbus3C 37 }

hmWanMbus3CVIF10		OBJECT-TYPE
			SYNTAX	INTEGER
			MAX-ACCESS	read-only
			STATUS	current
			::= { hmWanMbus3C 38 }

hmWanMbus3CValue10		OBJECT-TYPE
			SYNTAX	INTEGER
			MAX-ACCESS	read-only
			STATUS	current
			::= { hmWanMbus3C 39 }

hmWanMbus3CVIF11		OBJECT-TYPE
			SYNTAX	INTEGER
			MAX-ACCESS	read-only
			STATUS	current
			::= { hmWanMbus3C 40 }

hmWanMbus3CValue11		OBJECT-TYPE
			SYNTAX	INTEGER
			MAX-ACCESS	read-only
			STATUS	current
			::= { hmWanMbus3C 41 }

hmWanMbus3CVIF12		OBJECT-TYPE
			SYNTAX	INTEGER
			MAX-ACCESS	read-only
			STATUS	current
			::= { hmWanMbus3C 42 }

hmWanMbus3CValue12		OBJECT-TYPE
			SYNTAX	INTEGER
			MAX-ACCESS	read-only
			STATUS	current
			::= { hmWanMbus3C 43 }

hmWanMbus3CVIF13		OBJECT-TYPE
			SYNTAX	INTEGER
			MAX-ACCESS	read-only
			STATUS	current
			::= { hmWanMbus3C 44 }

hmWanMbus3CValue13		OBJECT-TYPE
			SYNTAX	INTEGER
			MAX-ACCESS	read-only
			STATUS	current
			::= { hmWanMbus3C 45 }

hmWanMbus3CVIF14		OBJECT-TYPE
			SYNTAX	INTEGER
			MAX-ACCESS	read-only
			STATUS	current
			::= { hmWanMbus3C 46 }

hmWanMbus3CValue14		OBJECT-TYPE
			SYNTAX	INTEGER
			MAX-ACCESS	read-only
			STATUS	current
			::= { hmWanMbus3C 47 }

hmWanMbus3CVIF15		OBJECT-TYPE
			SYNTAX	INTEGER
			MAX-ACCESS	read-only
			STATUS	current
			::= { hmWanMbus3C 48 }

hmWanMbus3CValue15		OBJECT-TYPE
			SYNTAX	INTEGER
			MAX-ACCESS	read-only
			STATUS	current
			::= { hmWanMbus3C 49 }

hmWanMbus3CVIF16		OBJECT-TYPE
			SYNTAX	INTEGER
			MAX-ACCESS	read-only
			STATUS	current
			::= { hmWanMbus3C 50 }

hmWanMbus3CValue16		OBJECT-TYPE
			SYNTAX	INTEGER
			MAX-ACCESS	read-only
			STATUS	current
			::= { hmWanMbus3C 51 }

hmWanMbus3CVIF17		OBJECT-TYPE
			SYNTAX	INTEGER
			MAX-ACCESS	read-only
			STATUS	current
			::= { hmWanMbus3C 52 }

hmWanMbus3CValue17		OBJECT-TYPE
			SYNTAX	INTEGER
			MAX-ACCESS	read-only
			STATUS	current
			::= { hmWanMbus3C 53 }

hmWanMbus3CVIF18		OBJECT-TYPE
			SYNTAX	INTEGER
			MAX-ACCESS	read-only
			STATUS	current
			::= { hmWanMbus3C 54 }

hmWanMbus3CValue18		OBJECT-TYPE
			SYNTAX	INTEGER
			MAX-ACCESS	read-only
			STATUS	current
			::= { hmWanMbus3C 55 }

hmWanMbus3CVIF19		OBJECT-TYPE
			SYNTAX	INTEGER
			MAX-ACCESS	read-only
			STATUS	current
			::= { hmWanMbus3C 56 }

hmWanMbus3CValue19		OBJECT-TYPE
			SYNTAX	INTEGER
			MAX-ACCESS	read-only
			STATUS	current
			::= { hmWanMbus3C 57 }

hmWanMbus3CVIF1A		OBJECT-TYPE
			SYNTAX	INTEGER
			MAX-ACCESS	read-only
			STATUS	current
			::= { hmWanMbus3C 58 }

hmWanMbus3CValue1A		OBJECT-TYPE
			SYNTAX	INTEGER
			MAX-ACCESS	read-only
			STATUS	current
			::= { hmWanMbus3C 59 }

hmWanMbus3CVIF1B		OBJECT-TYPE
			SYNTAX	INTEGER
			MAX-ACCESS	read-only
			STATUS	current
			::= { hmWanMbus3C 60 }

hmWanMbus3CValue1B		OBJECT-TYPE
			SYNTAX	INTEGER
			MAX-ACCESS	read-only
			STATUS	current
			::= { hmWanMbus3C 61 }

hmWanMbus3CVIF1C		OBJECT-TYPE
			SYNTAX	INTEGER
			MAX-ACCESS	read-only
			STATUS	current
			::= { hmWanMbus3C 62 }

hmWanMbus3CValue1C		OBJECT-TYPE
			SYNTAX	INTEGER
			MAX-ACCESS	read-only
			STATUS	current
			::= { hmWanMbus3C 63 }

hmWanMbus3CVIF1D		OBJECT-TYPE
			SYNTAX	INTEGER
			MAX-ACCESS	read-only
			STATUS	current
			::= { hmWanMbus3C 64 }

hmWanMbus3CValue1D		OBJECT-TYPE
			SYNTAX	INTEGER
			MAX-ACCESS	read-only
			STATUS	current
			::= { hmWanMbus3C 65 }

hmWanMbus3CVIF1E		OBJECT-TYPE
			SYNTAX	INTEGER
			MAX-ACCESS	read-only
			STATUS	current
			::= { hmWanMbus3C 66 }

hmWanMbus3CValue1E		OBJECT-TYPE
			SYNTAX	INTEGER
			MAX-ACCESS	read-only
			STATUS	current
			::= { hmWanMbus3C 67 }

hmWanMbus3CVIF1F		OBJECT-TYPE
			SYNTAX	INTEGER
			MAX-ACCESS	read-only
			STATUS	current
			::= { hmWanMbus3C 68 }

hmWanMbus3CValue1F		OBJECT-TYPE
			SYNTAX	INTEGER
			MAX-ACCESS	read-only
			STATUS	current
			::= { hmWanMbus3C 69 }

hmWanMbus3CVIF20		OBJECT-TYPE
			SYNTAX	INTEGER
			MAX-ACCESS	read-only
			STATUS	current
			::= { hmWanMbus3C 70 }

hmWanMbus3CValue20		OBJECT-TYPE
			SYNTAX	INTEGER
			MAX-ACCESS	read-only
			STATUS	current
			::= { hmWanMbus3C 71 }

hmWanMbus3CVIF21		OBJECT-TYPE
			SYNTAX	INTEGER
			MAX-ACCESS	read-only
			STATUS	current
			::= { hmWanMbus3C 72 }

hmWanMbus3CValue21		OBJECT-TYPE
			SYNTAX	INTEGER
			MAX-ACCESS	read-only
			STATUS	current
			::= { hmWanMbus3C 73 }

hmWanMbus3CVIF22		OBJECT-TYPE
			SYNTAX	INTEGER
			MAX-ACCESS	read-only
			STATUS	current
			::= { hmWanMbus3C 74 }

hmWanMbus3CValue22		OBJECT-TYPE
			SYNTAX	INTEGER
			MAX-ACCESS	read-only
			STATUS	current
			::= { hmWanMbus3C 75 }

hmWanMbus3CVIF23		OBJECT-TYPE
			SYNTAX	INTEGER
			MAX-ACCESS	read-only
			STATUS	current
			::= { hmWanMbus3C 76 }

hmWanMbus3CValue23		OBJECT-TYPE
			SYNTAX	INTEGER
			MAX-ACCESS	read-only
			STATUS	current
			::= { hmWanMbus3C 77 }

hmWanMbus3CVIF24		OBJECT-TYPE
			SYNTAX	INTEGER
			MAX-ACCESS	read-only
			STATUS	current
			::= { hmWanMbus3C 78 }

hmWanMbus3CValue24		OBJECT-TYPE
			SYNTAX	INTEGER
			MAX-ACCESS	read-only
			STATUS	current
			::= { hmWanMbus3C 79 }

hmWanMbus3CVIF25		OBJECT-TYPE
			SYNTAX	INTEGER
			MAX-ACCESS	read-only
			STATUS	current
			::= { hmWanMbus3C 80 }

hmWanMbus3CValue25		OBJECT-TYPE
			SYNTAX	INTEGER
			MAX-ACCESS	read-only
			STATUS	current
			::= { hmWanMbus3C 81 }

hmWanMbus3CVIF26		OBJECT-TYPE
			SYNTAX	INTEGER
			MAX-ACCESS	read-only
			STATUS	current
			::= { hmWanMbus3C 82 }

hmWanMbus3CValue26		OBJECT-TYPE
			SYNTAX	INTEGER
			MAX-ACCESS	read-only
			STATUS	current
			::= { hmWanMbus3C 83 }

hmWanMbus3CVIF27		OBJECT-TYPE
			SYNTAX	INTEGER
			MAX-ACCESS	read-only
			STATUS	current
			::= { hmWanMbus3C 84 }

hmWanMbus3CValue27		OBJECT-TYPE
			SYNTAX	INTEGER
			MAX-ACCESS	read-only
			STATUS	current
			::= { hmWanMbus3C 85 }

hmWanMbus3CVIF28		OBJECT-TYPE
			SYNTAX	INTEGER
			MAX-ACCESS	read-only
			STATUS	current
			::= { hmWanMbus3C 86 }

hmWanMbus3CValue28		OBJECT-TYPE
			SYNTAX	INTEGER
			MAX-ACCESS	read-only
			STATUS	current
			::= { hmWanMbus3C 87 }

hmWanMbus3CVIF29		OBJECT-TYPE
			SYNTAX	INTEGER
			MAX-ACCESS	read-only
			STATUS	current
			::= { hmWanMbus3C 88 }

hmWanMbus3CValue29		OBJECT-TYPE
			SYNTAX	INTEGER
			MAX-ACCESS	read-only
			STATUS	current
			::= { hmWanMbus3C 89 }

hmWanMbus3CVIF2A		OBJECT-TYPE
			SYNTAX	INTEGER
			MAX-ACCESS	read-only
			STATUS	current
			::= { hmWanMbus3C 90 }

hmWanMbus3CValue2A		OBJECT-TYPE
			SYNTAX	INTEGER
			MAX-ACCESS	read-only
			STATUS	current
			::= { hmWanMbus3C 91 }

hmWanMbus3CVIF2B		OBJECT-TYPE
			SYNTAX	INTEGER
			MAX-ACCESS	read-only
			STATUS	current
			::= { hmWanMbus3C 92 }

hmWanMbus3CValue2B		OBJECT-TYPE
			SYNTAX	INTEGER
			MAX-ACCESS	read-only
			STATUS	current
			::= { hmWanMbus3C 93 }

hmWanMbus3CVIF2C		OBJECT-TYPE
			SYNTAX	INTEGER
			MAX-ACCESS	read-only
			STATUS	current
			::= { hmWanMbus3C 94 }

hmWanMbus3CValue2C		OBJECT-TYPE
			SYNTAX	INTEGER
			MAX-ACCESS	read-only
			STATUS	current
			::= { hmWanMbus3C 95 }

hmWanMbus3CVIF2D		OBJECT-TYPE
			SYNTAX	INTEGER
			MAX-ACCESS	read-only
			STATUS	current
			::= { hmWanMbus3C 96 }

hmWanMbus3CValue2D		OBJECT-TYPE
			SYNTAX	INTEGER
			MAX-ACCESS	read-only
			STATUS	current
			::= { hmWanMbus3C 97 }

hmWanMbus3CVIF2E		OBJECT-TYPE
			SYNTAX	INTEGER
			MAX-ACCESS	read-only
			STATUS	current
			::= { hmWanMbus3C 98 }

hmWanMbus3CValue2E		OBJECT-TYPE
			SYNTAX	INTEGER
			MAX-ACCESS	read-only
			STATUS	current
			::= { hmWanMbus3C 99 }

hmWanMbus3CVIF2F		OBJECT-TYPE
			SYNTAX	INTEGER
			MAX-ACCESS	read-only
			STATUS	current
			::= { hmWanMbus3C 100 }

hmWanMbus3CValue2F		OBJECT-TYPE
			SYNTAX	INTEGER
			MAX-ACCESS	read-only
			STATUS	current
			::= { hmWanMbus3C 101 }

hmWanMbus3D			OBJECT IDENTIFIER ::= { hmWanMbus 61 }

hmWanMbus3DIdNumber		OBJECT-TYPE
			SYNTAX	Gauge32
			MAX-ACCESS	read-only
			STATUS	current
			::= { hmWanMbus3D 1 }

hmWanMbus3DManufacturer	OBJECT-TYPE
			SYNTAX	Gauge32
			MAX-ACCESS	read-only
			STATUS	current
			::= { hmWanMbus3D 2 }

hmWanMbus3DVersion		OBJECT-TYPE
			SYNTAX	Gauge32
			MAX-ACCESS	read-only
			STATUS	current
			::= { hmWanMbus3D 3 }

hmWanMbus3DMedium		OBJECT-TYPE
			SYNTAX	Gauge32
			MAX-ACCESS	read-only
			STATUS	current
			::= { hmWanMbus3D 4 }

hmWanMbus3DStatus		OBJECT-TYPE
			SYNTAX	Gauge32
			MAX-ACCESS	read-only
			STATUS	current
			::= { hmWanMbus3D 5 }

hmWanMbus3DVIF00		OBJECT-TYPE
			SYNTAX	INTEGER
			MAX-ACCESS	read-only
			STATUS	current
			::= { hmWanMbus3D 6 }

hmWanMbus3DValue00		OBJECT-TYPE
			SYNTAX	INTEGER
			MAX-ACCESS	read-only
			STATUS	current
			::= { hmWanMbus3D 7 }

hmWanMbus3DVIF01		OBJECT-TYPE
			SYNTAX	INTEGER
			MAX-ACCESS	read-only
			STATUS	current
			::= { hmWanMbus3D 8 }

hmWanMbus3DValue01		OBJECT-TYPE
			SYNTAX	INTEGER
			MAX-ACCESS	read-only
			STATUS	current
			::= { hmWanMbus3D 9 }

hmWanMbus3DVIF02		OBJECT-TYPE
			SYNTAX	INTEGER
			MAX-ACCESS	read-only
			STATUS	current
			::= { hmWanMbus3D 10 }

hmWanMbus3DValue02		OBJECT-TYPE
			SYNTAX	INTEGER
			MAX-ACCESS	read-only
			STATUS	current
			::= { hmWanMbus3D 11 }

hmWanMbus3DVIF03		OBJECT-TYPE
			SYNTAX	INTEGER
			MAX-ACCESS	read-only
			STATUS	current
			::= { hmWanMbus3D 12 }

hmWanMbus3DValue03		OBJECT-TYPE
			SYNTAX	INTEGER
			MAX-ACCESS	read-only
			STATUS	current
			::= { hmWanMbus3D 13 }

hmWanMbus3DVIF04		OBJECT-TYPE
			SYNTAX	INTEGER
			MAX-ACCESS	read-only
			STATUS	current
			::= { hmWanMbus3D 14 }

hmWanMbus3DValue04		OBJECT-TYPE
			SYNTAX	INTEGER
			MAX-ACCESS	read-only
			STATUS	current
			::= { hmWanMbus3D 15 }

hmWanMbus3DVIF05		OBJECT-TYPE
			SYNTAX	INTEGER
			MAX-ACCESS	read-only
			STATUS	current
			::= { hmWanMbus3D 16 }

hmWanMbus3DValue05		OBJECT-TYPE
			SYNTAX	INTEGER
			MAX-ACCESS	read-only
			STATUS	current
			::= { hmWanMbus3D 17 }

hmWanMbus3DVIF06		OBJECT-TYPE
			SYNTAX	INTEGER
			MAX-ACCESS	read-only
			STATUS	current
			::= { hmWanMbus3D 18 }

hmWanMbus3DValue06		OBJECT-TYPE
			SYNTAX	INTEGER
			MAX-ACCESS	read-only
			STATUS	current
			::= { hmWanMbus3D 19 }

hmWanMbus3DVIF07		OBJECT-TYPE
			SYNTAX	INTEGER
			MAX-ACCESS	read-only
			STATUS	current
			::= { hmWanMbus3D 20 }

hmWanMbus3DValue07		OBJECT-TYPE
			SYNTAX	INTEGER
			MAX-ACCESS	read-only
			STATUS	current
			::= { hmWanMbus3D 21 }

hmWanMbus3DVIF08		OBJECT-TYPE
			SYNTAX	INTEGER
			MAX-ACCESS	read-only
			STATUS	current
			::= { hmWanMbus3D 22 }

hmWanMbus3DValue08		OBJECT-TYPE
			SYNTAX	INTEGER
			MAX-ACCESS	read-only
			STATUS	current
			::= { hmWanMbus3D 23 }

hmWanMbus3DVIF09		OBJECT-TYPE
			SYNTAX	INTEGER
			MAX-ACCESS	read-only
			STATUS	current
			::= { hmWanMbus3D 24 }

hmWanMbus3DValue09		OBJECT-TYPE
			SYNTAX	INTEGER
			MAX-ACCESS	read-only
			STATUS	current
			::= { hmWanMbus3D 25 }

hmWanMbus3DVIF0A		OBJECT-TYPE
			SYNTAX	INTEGER
			MAX-ACCESS	read-only
			STATUS	current
			::= { hmWanMbus3D 26 }

hmWanMbus3DValue0A		OBJECT-TYPE
			SYNTAX	INTEGER
			MAX-ACCESS	read-only
			STATUS	current
			::= { hmWanMbus3D 27 }

hmWanMbus3DVIF0B		OBJECT-TYPE
			SYNTAX	INTEGER
			MAX-ACCESS	read-only
			STATUS	current
			::= { hmWanMbus3D 28 }

hmWanMbus3DValue0B		OBJECT-TYPE
			SYNTAX	INTEGER
			MAX-ACCESS	read-only
			STATUS	current
			::= { hmWanMbus3D 29 }

hmWanMbus3DVIF0C		OBJECT-TYPE
			SYNTAX	INTEGER
			MAX-ACCESS	read-only
			STATUS	current
			::= { hmWanMbus3D 30 }

hmWanMbus3DValue0C		OBJECT-TYPE
			SYNTAX	INTEGER
			MAX-ACCESS	read-only
			STATUS	current
			::= { hmWanMbus3D 31 }

hmWanMbus3DVIF0D		OBJECT-TYPE
			SYNTAX	INTEGER
			MAX-ACCESS	read-only
			STATUS	current
			::= { hmWanMbus3D 32 }

hmWanMbus3DValue0D		OBJECT-TYPE
			SYNTAX	INTEGER
			MAX-ACCESS	read-only
			STATUS	current
			::= { hmWanMbus3D 33 }

hmWanMbus3DVIF0E		OBJECT-TYPE
			SYNTAX	INTEGER
			MAX-ACCESS	read-only
			STATUS	current
			::= { hmWanMbus3D 34 }

hmWanMbus3DValue0E		OBJECT-TYPE
			SYNTAX	INTEGER
			MAX-ACCESS	read-only
			STATUS	current
			::= { hmWanMbus3D 35 }

hmWanMbus3DVIF0F		OBJECT-TYPE
			SYNTAX	INTEGER
			MAX-ACCESS	read-only
			STATUS	current
			::= { hmWanMbus3D 36 }

hmWanMbus3DValue0F		OBJECT-TYPE
			SYNTAX	INTEGER
			MAX-ACCESS	read-only
			STATUS	current
			::= { hmWanMbus3D 37 }

hmWanMbus3DVIF10		OBJECT-TYPE
			SYNTAX	INTEGER
			MAX-ACCESS	read-only
			STATUS	current
			::= { hmWanMbus3D 38 }

hmWanMbus3DValue10		OBJECT-TYPE
			SYNTAX	INTEGER
			MAX-ACCESS	read-only
			STATUS	current
			::= { hmWanMbus3D 39 }

hmWanMbus3DVIF11		OBJECT-TYPE
			SYNTAX	INTEGER
			MAX-ACCESS	read-only
			STATUS	current
			::= { hmWanMbus3D 40 }

hmWanMbus3DValue11		OBJECT-TYPE
			SYNTAX	INTEGER
			MAX-ACCESS	read-only
			STATUS	current
			::= { hmWanMbus3D 41 }

hmWanMbus3DVIF12		OBJECT-TYPE
			SYNTAX	INTEGER
			MAX-ACCESS	read-only
			STATUS	current
			::= { hmWanMbus3D 42 }

hmWanMbus3DValue12		OBJECT-TYPE
			SYNTAX	INTEGER
			MAX-ACCESS	read-only
			STATUS	current
			::= { hmWanMbus3D 43 }

hmWanMbus3DVIF13		OBJECT-TYPE
			SYNTAX	INTEGER
			MAX-ACCESS	read-only
			STATUS	current
			::= { hmWanMbus3D 44 }

hmWanMbus3DValue13		OBJECT-TYPE
			SYNTAX	INTEGER
			MAX-ACCESS	read-only
			STATUS	current
			::= { hmWanMbus3D 45 }

hmWanMbus3DVIF14		OBJECT-TYPE
			SYNTAX	INTEGER
			MAX-ACCESS	read-only
			STATUS	current
			::= { hmWanMbus3D 46 }

hmWanMbus3DValue14		OBJECT-TYPE
			SYNTAX	INTEGER
			MAX-ACCESS	read-only
			STATUS	current
			::= { hmWanMbus3D 47 }

hmWanMbus3DVIF15		OBJECT-TYPE
			SYNTAX	INTEGER
			MAX-ACCESS	read-only
			STATUS	current
			::= { hmWanMbus3D 48 }

hmWanMbus3DValue15		OBJECT-TYPE
			SYNTAX	INTEGER
			MAX-ACCESS	read-only
			STATUS	current
			::= { hmWanMbus3D 49 }

hmWanMbus3DVIF16		OBJECT-TYPE
			SYNTAX	INTEGER
			MAX-ACCESS	read-only
			STATUS	current
			::= { hmWanMbus3D 50 }

hmWanMbus3DValue16		OBJECT-TYPE
			SYNTAX	INTEGER
			MAX-ACCESS	read-only
			STATUS	current
			::= { hmWanMbus3D 51 }

hmWanMbus3DVIF17		OBJECT-TYPE
			SYNTAX	INTEGER
			MAX-ACCESS	read-only
			STATUS	current
			::= { hmWanMbus3D 52 }

hmWanMbus3DValue17		OBJECT-TYPE
			SYNTAX	INTEGER
			MAX-ACCESS	read-only
			STATUS	current
			::= { hmWanMbus3D 53 }

hmWanMbus3DVIF18		OBJECT-TYPE
			SYNTAX	INTEGER
			MAX-ACCESS	read-only
			STATUS	current
			::= { hmWanMbus3D 54 }

hmWanMbus3DValue18		OBJECT-TYPE
			SYNTAX	INTEGER
			MAX-ACCESS	read-only
			STATUS	current
			::= { hmWanMbus3D 55 }

hmWanMbus3DVIF19		OBJECT-TYPE
			SYNTAX	INTEGER
			MAX-ACCESS	read-only
			STATUS	current
			::= { hmWanMbus3D 56 }

hmWanMbus3DValue19		OBJECT-TYPE
			SYNTAX	INTEGER
			MAX-ACCESS	read-only
			STATUS	current
			::= { hmWanMbus3D 57 }

hmWanMbus3DVIF1A		OBJECT-TYPE
			SYNTAX	INTEGER
			MAX-ACCESS	read-only
			STATUS	current
			::= { hmWanMbus3D 58 }

hmWanMbus3DValue1A		OBJECT-TYPE
			SYNTAX	INTEGER
			MAX-ACCESS	read-only
			STATUS	current
			::= { hmWanMbus3D 59 }

hmWanMbus3DVIF1B		OBJECT-TYPE
			SYNTAX	INTEGER
			MAX-ACCESS	read-only
			STATUS	current
			::= { hmWanMbus3D 60 }

hmWanMbus3DValue1B		OBJECT-TYPE
			SYNTAX	INTEGER
			MAX-ACCESS	read-only
			STATUS	current
			::= { hmWanMbus3D 61 }

hmWanMbus3DVIF1C		OBJECT-TYPE
			SYNTAX	INTEGER
			MAX-ACCESS	read-only
			STATUS	current
			::= { hmWanMbus3D 62 }

hmWanMbus3DValue1C		OBJECT-TYPE
			SYNTAX	INTEGER
			MAX-ACCESS	read-only
			STATUS	current
			::= { hmWanMbus3D 63 }

hmWanMbus3DVIF1D		OBJECT-TYPE
			SYNTAX	INTEGER
			MAX-ACCESS	read-only
			STATUS	current
			::= { hmWanMbus3D 64 }

hmWanMbus3DValue1D		OBJECT-TYPE
			SYNTAX	INTEGER
			MAX-ACCESS	read-only
			STATUS	current
			::= { hmWanMbus3D 65 }

hmWanMbus3DVIF1E		OBJECT-TYPE
			SYNTAX	INTEGER
			MAX-ACCESS	read-only
			STATUS	current
			::= { hmWanMbus3D 66 }

hmWanMbus3DValue1E		OBJECT-TYPE
			SYNTAX	INTEGER
			MAX-ACCESS	read-only
			STATUS	current
			::= { hmWanMbus3D 67 }

hmWanMbus3DVIF1F		OBJECT-TYPE
			SYNTAX	INTEGER
			MAX-ACCESS	read-only
			STATUS	current
			::= { hmWanMbus3D 68 }

hmWanMbus3DValue1F		OBJECT-TYPE
			SYNTAX	INTEGER
			MAX-ACCESS	read-only
			STATUS	current
			::= { hmWanMbus3D 69 }

hmWanMbus3DVIF20		OBJECT-TYPE
			SYNTAX	INTEGER
			MAX-ACCESS	read-only
			STATUS	current
			::= { hmWanMbus3D 70 }

hmWanMbus3DValue20		OBJECT-TYPE
			SYNTAX	INTEGER
			MAX-ACCESS	read-only
			STATUS	current
			::= { hmWanMbus3D 71 }

hmWanMbus3DVIF21		OBJECT-TYPE
			SYNTAX	INTEGER
			MAX-ACCESS	read-only
			STATUS	current
			::= { hmWanMbus3D 72 }

hmWanMbus3DValue21		OBJECT-TYPE
			SYNTAX	INTEGER
			MAX-ACCESS	read-only
			STATUS	current
			::= { hmWanMbus3D 73 }

hmWanMbus3DVIF22		OBJECT-TYPE
			SYNTAX	INTEGER
			MAX-ACCESS	read-only
			STATUS	current
			::= { hmWanMbus3D 74 }

hmWanMbus3DValue22		OBJECT-TYPE
			SYNTAX	INTEGER
			MAX-ACCESS	read-only
			STATUS	current
			::= { hmWanMbus3D 75 }

hmWanMbus3DVIF23		OBJECT-TYPE
			SYNTAX	INTEGER
			MAX-ACCESS	read-only
			STATUS	current
			::= { hmWanMbus3D 76 }

hmWanMbus3DValue23		OBJECT-TYPE
			SYNTAX	INTEGER
			MAX-ACCESS	read-only
			STATUS	current
			::= { hmWanMbus3D 77 }

hmWanMbus3DVIF24		OBJECT-TYPE
			SYNTAX	INTEGER
			MAX-ACCESS	read-only
			STATUS	current
			::= { hmWanMbus3D 78 }

hmWanMbus3DValue24		OBJECT-TYPE
			SYNTAX	INTEGER
			MAX-ACCESS	read-only
			STATUS	current
			::= { hmWanMbus3D 79 }

hmWanMbus3DVIF25		OBJECT-TYPE
			SYNTAX	INTEGER
			MAX-ACCESS	read-only
			STATUS	current
			::= { hmWanMbus3D 80 }

hmWanMbus3DValue25		OBJECT-TYPE
			SYNTAX	INTEGER
			MAX-ACCESS	read-only
			STATUS	current
			::= { hmWanMbus3D 81 }

hmWanMbus3DVIF26		OBJECT-TYPE
			SYNTAX	INTEGER
			MAX-ACCESS	read-only
			STATUS	current
			::= { hmWanMbus3D 82 }

hmWanMbus3DValue26		OBJECT-TYPE
			SYNTAX	INTEGER
			MAX-ACCESS	read-only
			STATUS	current
			::= { hmWanMbus3D 83 }

hmWanMbus3DVIF27		OBJECT-TYPE
			SYNTAX	INTEGER
			MAX-ACCESS	read-only
			STATUS	current
			::= { hmWanMbus3D 84 }

hmWanMbus3DValue27		OBJECT-TYPE
			SYNTAX	INTEGER
			MAX-ACCESS	read-only
			STATUS	current
			::= { hmWanMbus3D 85 }

hmWanMbus3DVIF28		OBJECT-TYPE
			SYNTAX	INTEGER
			MAX-ACCESS	read-only
			STATUS	current
			::= { hmWanMbus3D 86 }

hmWanMbus3DValue28		OBJECT-TYPE
			SYNTAX	INTEGER
			MAX-ACCESS	read-only
			STATUS	current
			::= { hmWanMbus3D 87 }

hmWanMbus3DVIF29		OBJECT-TYPE
			SYNTAX	INTEGER
			MAX-ACCESS	read-only
			STATUS	current
			::= { hmWanMbus3D 88 }

hmWanMbus3DValue29		OBJECT-TYPE
			SYNTAX	INTEGER
			MAX-ACCESS	read-only
			STATUS	current
			::= { hmWanMbus3D 89 }

hmWanMbus3DVIF2A		OBJECT-TYPE
			SYNTAX	INTEGER
			MAX-ACCESS	read-only
			STATUS	current
			::= { hmWanMbus3D 90 }

hmWanMbus3DValue2A		OBJECT-TYPE
			SYNTAX	INTEGER
			MAX-ACCESS	read-only
			STATUS	current
			::= { hmWanMbus3D 91 }

hmWanMbus3DVIF2B		OBJECT-TYPE
			SYNTAX	INTEGER
			MAX-ACCESS	read-only
			STATUS	current
			::= { hmWanMbus3D 92 }

hmWanMbus3DValue2B		OBJECT-TYPE
			SYNTAX	INTEGER
			MAX-ACCESS	read-only
			STATUS	current
			::= { hmWanMbus3D 93 }

hmWanMbus3DVIF2C		OBJECT-TYPE
			SYNTAX	INTEGER
			MAX-ACCESS	read-only
			STATUS	current
			::= { hmWanMbus3D 94 }

hmWanMbus3DValue2C		OBJECT-TYPE
			SYNTAX	INTEGER
			MAX-ACCESS	read-only
			STATUS	current
			::= { hmWanMbus3D 95 }

hmWanMbus3DVIF2D		OBJECT-TYPE
			SYNTAX	INTEGER
			MAX-ACCESS	read-only
			STATUS	current
			::= { hmWanMbus3D 96 }

hmWanMbus3DValue2D		OBJECT-TYPE
			SYNTAX	INTEGER
			MAX-ACCESS	read-only
			STATUS	current
			::= { hmWanMbus3D 97 }

hmWanMbus3DVIF2E		OBJECT-TYPE
			SYNTAX	INTEGER
			MAX-ACCESS	read-only
			STATUS	current
			::= { hmWanMbus3D 98 }

hmWanMbus3DValue2E		OBJECT-TYPE
			SYNTAX	INTEGER
			MAX-ACCESS	read-only
			STATUS	current
			::= { hmWanMbus3D 99 }

hmWanMbus3DVIF2F		OBJECT-TYPE
			SYNTAX	INTEGER
			MAX-ACCESS	read-only
			STATUS	current
			::= { hmWanMbus3D 100 }

hmWanMbus3DValue2F		OBJECT-TYPE
			SYNTAX	INTEGER
			MAX-ACCESS	read-only
			STATUS	current
			::= { hmWanMbus3D 101 }

hmWanMbus3E			OBJECT IDENTIFIER ::= { hmWanMbus 62 }

hmWanMbus3EIdNumber		OBJECT-TYPE
			SYNTAX	Gauge32
			MAX-ACCESS	read-only
			STATUS	current
			::= { hmWanMbus3E 1 }

hmWanMbus3EManufacturer	OBJECT-TYPE
			SYNTAX	Gauge32
			MAX-ACCESS	read-only
			STATUS	current
			::= { hmWanMbus3E 2 }

hmWanMbus3EVersion		OBJECT-TYPE
			SYNTAX	Gauge32
			MAX-ACCESS	read-only
			STATUS	current
			::= { hmWanMbus3E 3 }

hmWanMbus3EMedium		OBJECT-TYPE
			SYNTAX	Gauge32
			MAX-ACCESS	read-only
			STATUS	current
			::= { hmWanMbus3E 4 }

hmWanMbus3EStatus		OBJECT-TYPE
			SYNTAX	Gauge32
			MAX-ACCESS	read-only
			STATUS	current
			::= { hmWanMbus3E 5 }

hmWanMbus3EVIF00		OBJECT-TYPE
			SYNTAX	INTEGER
			MAX-ACCESS	read-only
			STATUS	current
			::= { hmWanMbus3E 6 }

hmWanMbus3EValue00		OBJECT-TYPE
			SYNTAX	INTEGER
			MAX-ACCESS	read-only
			STATUS	current
			::= { hmWanMbus3E 7 }

hmWanMbus3EVIF01		OBJECT-TYPE
			SYNTAX	INTEGER
			MAX-ACCESS	read-only
			STATUS	current
			::= { hmWanMbus3E 8 }

hmWanMbus3EValue01		OBJECT-TYPE
			SYNTAX	INTEGER
			MAX-ACCESS	read-only
			STATUS	current
			::= { hmWanMbus3E 9 }

hmWanMbus3EVIF02		OBJECT-TYPE
			SYNTAX	INTEGER
			MAX-ACCESS	read-only
			STATUS	current
			::= { hmWanMbus3E 10 }

hmWanMbus3EValue02		OBJECT-TYPE
			SYNTAX	INTEGER
			MAX-ACCESS	read-only
			STATUS	current
			::= { hmWanMbus3E 11 }

hmWanMbus3EVIF03		OBJECT-TYPE
			SYNTAX	INTEGER
			MAX-ACCESS	read-only
			STATUS	current
			::= { hmWanMbus3E 12 }

hmWanMbus3EValue03		OBJECT-TYPE
			SYNTAX	INTEGER
			MAX-ACCESS	read-only
			STATUS	current
			::= { hmWanMbus3E 13 }

hmWanMbus3EVIF04		OBJECT-TYPE
			SYNTAX	INTEGER
			MAX-ACCESS	read-only
			STATUS	current
			::= { hmWanMbus3E 14 }

hmWanMbus3EValue04		OBJECT-TYPE
			SYNTAX	INTEGER
			MAX-ACCESS	read-only
			STATUS	current
			::= { hmWanMbus3E 15 }

hmWanMbus3EVIF05		OBJECT-TYPE
			SYNTAX	INTEGER
			MAX-ACCESS	read-only
			STATUS	current
			::= { hmWanMbus3E 16 }

hmWanMbus3EValue05		OBJECT-TYPE
			SYNTAX	INTEGER
			MAX-ACCESS	read-only
			STATUS	current
			::= { hmWanMbus3E 17 }

hmWanMbus3EVIF06		OBJECT-TYPE
			SYNTAX	INTEGER
			MAX-ACCESS	read-only
			STATUS	current
			::= { hmWanMbus3E 18 }

hmWanMbus3EValue06		OBJECT-TYPE
			SYNTAX	INTEGER
			MAX-ACCESS	read-only
			STATUS	current
			::= { hmWanMbus3E 19 }

hmWanMbus3EVIF07		OBJECT-TYPE
			SYNTAX	INTEGER
			MAX-ACCESS	read-only
			STATUS	current
			::= { hmWanMbus3E 20 }

hmWanMbus3EValue07		OBJECT-TYPE
			SYNTAX	INTEGER
			MAX-ACCESS	read-only
			STATUS	current
			::= { hmWanMbus3E 21 }

hmWanMbus3EVIF08		OBJECT-TYPE
			SYNTAX	INTEGER
			MAX-ACCESS	read-only
			STATUS	current
			::= { hmWanMbus3E 22 }

hmWanMbus3EValue08		OBJECT-TYPE
			SYNTAX	INTEGER
			MAX-ACCESS	read-only
			STATUS	current
			::= { hmWanMbus3E 23 }

hmWanMbus3EVIF09		OBJECT-TYPE
			SYNTAX	INTEGER
			MAX-ACCESS	read-only
			STATUS	current
			::= { hmWanMbus3E 24 }

hmWanMbus3EValue09		OBJECT-TYPE
			SYNTAX	INTEGER
			MAX-ACCESS	read-only
			STATUS	current
			::= { hmWanMbus3E 25 }

hmWanMbus3EVIF0A		OBJECT-TYPE
			SYNTAX	INTEGER
			MAX-ACCESS	read-only
			STATUS	current
			::= { hmWanMbus3E 26 }

hmWanMbus3EValue0A		OBJECT-TYPE
			SYNTAX	INTEGER
			MAX-ACCESS	read-only
			STATUS	current
			::= { hmWanMbus3E 27 }

hmWanMbus3EVIF0B		OBJECT-TYPE
			SYNTAX	INTEGER
			MAX-ACCESS	read-only
			STATUS	current
			::= { hmWanMbus3E 28 }

hmWanMbus3EValue0B		OBJECT-TYPE
			SYNTAX	INTEGER
			MAX-ACCESS	read-only
			STATUS	current
			::= { hmWanMbus3E 29 }

hmWanMbus3EVIF0C		OBJECT-TYPE
			SYNTAX	INTEGER
			MAX-ACCESS	read-only
			STATUS	current
			::= { hmWanMbus3E 30 }

hmWanMbus3EValue0C		OBJECT-TYPE
			SYNTAX	INTEGER
			MAX-ACCESS	read-only
			STATUS	current
			::= { hmWanMbus3E 31 }

hmWanMbus3EVIF0D		OBJECT-TYPE
			SYNTAX	INTEGER
			MAX-ACCESS	read-only
			STATUS	current
			::= { hmWanMbus3E 32 }

hmWanMbus3EValue0D		OBJECT-TYPE
			SYNTAX	INTEGER
			MAX-ACCESS	read-only
			STATUS	current
			::= { hmWanMbus3E 33 }

hmWanMbus3EVIF0E		OBJECT-TYPE
			SYNTAX	INTEGER
			MAX-ACCESS	read-only
			STATUS	current
			::= { hmWanMbus3E 34 }

hmWanMbus3EValue0E		OBJECT-TYPE
			SYNTAX	INTEGER
			MAX-ACCESS	read-only
			STATUS	current
			::= { hmWanMbus3E 35 }

hmWanMbus3EVIF0F		OBJECT-TYPE
			SYNTAX	INTEGER
			MAX-ACCESS	read-only
			STATUS	current
			::= { hmWanMbus3E 36 }

hmWanMbus3EValue0F		OBJECT-TYPE
			SYNTAX	INTEGER
			MAX-ACCESS	read-only
			STATUS	current
			::= { hmWanMbus3E 37 }

hmWanMbus3EVIF10		OBJECT-TYPE
			SYNTAX	INTEGER
			MAX-ACCESS	read-only
			STATUS	current
			::= { hmWanMbus3E 38 }

hmWanMbus3EValue10		OBJECT-TYPE
			SYNTAX	INTEGER
			MAX-ACCESS	read-only
			STATUS	current
			::= { hmWanMbus3E 39 }

hmWanMbus3EVIF11		OBJECT-TYPE
			SYNTAX	INTEGER
			MAX-ACCESS	read-only
			STATUS	current
			::= { hmWanMbus3E 40 }

hmWanMbus3EValue11		OBJECT-TYPE
			SYNTAX	INTEGER
			MAX-ACCESS	read-only
			STATUS	current
			::= { hmWanMbus3E 41 }

hmWanMbus3EVIF12		OBJECT-TYPE
			SYNTAX	INTEGER
			MAX-ACCESS	read-only
			STATUS	current
			::= { hmWanMbus3E 42 }

hmWanMbus3EValue12		OBJECT-TYPE
			SYNTAX	INTEGER
			MAX-ACCESS	read-only
			STATUS	current
			::= { hmWanMbus3E 43 }

hmWanMbus3EVIF13		OBJECT-TYPE
			SYNTAX	INTEGER
			MAX-ACCESS	read-only
			STATUS	current
			::= { hmWanMbus3E 44 }

hmWanMbus3EValue13		OBJECT-TYPE
			SYNTAX	INTEGER
			MAX-ACCESS	read-only
			STATUS	current
			::= { hmWanMbus3E 45 }

hmWanMbus3EVIF14		OBJECT-TYPE
			SYNTAX	INTEGER
			MAX-ACCESS	read-only
			STATUS	current
			::= { hmWanMbus3E 46 }

hmWanMbus3EValue14		OBJECT-TYPE
			SYNTAX	INTEGER
			MAX-ACCESS	read-only
			STATUS	current
			::= { hmWanMbus3E 47 }

hmWanMbus3EVIF15		OBJECT-TYPE
			SYNTAX	INTEGER
			MAX-ACCESS	read-only
			STATUS	current
			::= { hmWanMbus3E 48 }

hmWanMbus3EValue15		OBJECT-TYPE
			SYNTAX	INTEGER
			MAX-ACCESS	read-only
			STATUS	current
			::= { hmWanMbus3E 49 }

hmWanMbus3EVIF16		OBJECT-TYPE
			SYNTAX	INTEGER
			MAX-ACCESS	read-only
			STATUS	current
			::= { hmWanMbus3E 50 }

hmWanMbus3EValue16		OBJECT-TYPE
			SYNTAX	INTEGER
			MAX-ACCESS	read-only
			STATUS	current
			::= { hmWanMbus3E 51 }

hmWanMbus3EVIF17		OBJECT-TYPE
			SYNTAX	INTEGER
			MAX-ACCESS	read-only
			STATUS	current
			::= { hmWanMbus3E 52 }

hmWanMbus3EValue17		OBJECT-TYPE
			SYNTAX	INTEGER
			MAX-ACCESS	read-only
			STATUS	current
			::= { hmWanMbus3E 53 }

hmWanMbus3EVIF18		OBJECT-TYPE
			SYNTAX	INTEGER
			MAX-ACCESS	read-only
			STATUS	current
			::= { hmWanMbus3E 54 }

hmWanMbus3EValue18		OBJECT-TYPE
			SYNTAX	INTEGER
			MAX-ACCESS	read-only
			STATUS	current
			::= { hmWanMbus3E 55 }

hmWanMbus3EVIF19		OBJECT-TYPE
			SYNTAX	INTEGER
			MAX-ACCESS	read-only
			STATUS	current
			::= { hmWanMbus3E 56 }

hmWanMbus3EValue19		OBJECT-TYPE
			SYNTAX	INTEGER
			MAX-ACCESS	read-only
			STATUS	current
			::= { hmWanMbus3E 57 }

hmWanMbus3EVIF1A		OBJECT-TYPE
			SYNTAX	INTEGER
			MAX-ACCESS	read-only
			STATUS	current
			::= { hmWanMbus3E 58 }

hmWanMbus3EValue1A		OBJECT-TYPE
			SYNTAX	INTEGER
			MAX-ACCESS	read-only
			STATUS	current
			::= { hmWanMbus3E 59 }

hmWanMbus3EVIF1B		OBJECT-TYPE
			SYNTAX	INTEGER
			MAX-ACCESS	read-only
			STATUS	current
			::= { hmWanMbus3E 60 }

hmWanMbus3EValue1B		OBJECT-TYPE
			SYNTAX	INTEGER
			MAX-ACCESS	read-only
			STATUS	current
			::= { hmWanMbus3E 61 }

hmWanMbus3EVIF1C		OBJECT-TYPE
			SYNTAX	INTEGER
			MAX-ACCESS	read-only
			STATUS	current
			::= { hmWanMbus3E 62 }

hmWanMbus3EValue1C		OBJECT-TYPE
			SYNTAX	INTEGER
			MAX-ACCESS	read-only
			STATUS	current
			::= { hmWanMbus3E 63 }

hmWanMbus3EVIF1D		OBJECT-TYPE
			SYNTAX	INTEGER
			MAX-ACCESS	read-only
			STATUS	current
			::= { hmWanMbus3E 64 }

hmWanMbus3EValue1D		OBJECT-TYPE
			SYNTAX	INTEGER
			MAX-ACCESS	read-only
			STATUS	current
			::= { hmWanMbus3E 65 }

hmWanMbus3EVIF1E		OBJECT-TYPE
			SYNTAX	INTEGER
			MAX-ACCESS	read-only
			STATUS	current
			::= { hmWanMbus3E 66 }

hmWanMbus3EValue1E		OBJECT-TYPE
			SYNTAX	INTEGER
			MAX-ACCESS	read-only
			STATUS	current
			::= { hmWanMbus3E 67 }

hmWanMbus3EVIF1F		OBJECT-TYPE
			SYNTAX	INTEGER
			MAX-ACCESS	read-only
			STATUS	current
			::= { hmWanMbus3E 68 }

hmWanMbus3EValue1F		OBJECT-TYPE
			SYNTAX	INTEGER
			MAX-ACCESS	read-only
			STATUS	current
			::= { hmWanMbus3E 69 }

hmWanMbus3EVIF20		OBJECT-TYPE
			SYNTAX	INTEGER
			MAX-ACCESS	read-only
			STATUS	current
			::= { hmWanMbus3E 70 }

hmWanMbus3EValue20		OBJECT-TYPE
			SYNTAX	INTEGER
			MAX-ACCESS	read-only
			STATUS	current
			::= { hmWanMbus3E 71 }

hmWanMbus3EVIF21		OBJECT-TYPE
			SYNTAX	INTEGER
			MAX-ACCESS	read-only
			STATUS	current
			::= { hmWanMbus3E 72 }

hmWanMbus3EValue21		OBJECT-TYPE
			SYNTAX	INTEGER
			MAX-ACCESS	read-only
			STATUS	current
			::= { hmWanMbus3E 73 }

hmWanMbus3EVIF22		OBJECT-TYPE
			SYNTAX	INTEGER
			MAX-ACCESS	read-only
			STATUS	current
			::= { hmWanMbus3E 74 }

hmWanMbus3EValue22		OBJECT-TYPE
			SYNTAX	INTEGER
			MAX-ACCESS	read-only
			STATUS	current
			::= { hmWanMbus3E 75 }

hmWanMbus3EVIF23		OBJECT-TYPE
			SYNTAX	INTEGER
			MAX-ACCESS	read-only
			STATUS	current
			::= { hmWanMbus3E 76 }

hmWanMbus3EValue23		OBJECT-TYPE
			SYNTAX	INTEGER
			MAX-ACCESS	read-only
			STATUS	current
			::= { hmWanMbus3E 77 }

hmWanMbus3EVIF24		OBJECT-TYPE
			SYNTAX	INTEGER
			MAX-ACCESS	read-only
			STATUS	current
			::= { hmWanMbus3E 78 }

hmWanMbus3EValue24		OBJECT-TYPE
			SYNTAX	INTEGER
			MAX-ACCESS	read-only
			STATUS	current
			::= { hmWanMbus3E 79 }

hmWanMbus3EVIF25		OBJECT-TYPE
			SYNTAX	INTEGER
			MAX-ACCESS	read-only
			STATUS	current
			::= { hmWanMbus3E 80 }

hmWanMbus3EValue25		OBJECT-TYPE
			SYNTAX	INTEGER
			MAX-ACCESS	read-only
			STATUS	current
			::= { hmWanMbus3E 81 }

hmWanMbus3EVIF26		OBJECT-TYPE
			SYNTAX	INTEGER
			MAX-ACCESS	read-only
			STATUS	current
			::= { hmWanMbus3E 82 }

hmWanMbus3EValue26		OBJECT-TYPE
			SYNTAX	INTEGER
			MAX-ACCESS	read-only
			STATUS	current
			::= { hmWanMbus3E 83 }

hmWanMbus3EVIF27		OBJECT-TYPE
			SYNTAX	INTEGER
			MAX-ACCESS	read-only
			STATUS	current
			::= { hmWanMbus3E 84 }

hmWanMbus3EValue27		OBJECT-TYPE
			SYNTAX	INTEGER
			MAX-ACCESS	read-only
			STATUS	current
			::= { hmWanMbus3E 85 }

hmWanMbus3EVIF28		OBJECT-TYPE
			SYNTAX	INTEGER
			MAX-ACCESS	read-only
			STATUS	current
			::= { hmWanMbus3E 86 }

hmWanMbus3EValue28		OBJECT-TYPE
			SYNTAX	INTEGER
			MAX-ACCESS	read-only
			STATUS	current
			::= { hmWanMbus3E 87 }

hmWanMbus3EVIF29		OBJECT-TYPE
			SYNTAX	INTEGER
			MAX-ACCESS	read-only
			STATUS	current
			::= { hmWanMbus3E 88 }

hmWanMbus3EValue29		OBJECT-TYPE
			SYNTAX	INTEGER
			MAX-ACCESS	read-only
			STATUS	current
			::= { hmWanMbus3E 89 }

hmWanMbus3EVIF2A		OBJECT-TYPE
			SYNTAX	INTEGER
			MAX-ACCESS	read-only
			STATUS	current
			::= { hmWanMbus3E 90 }

hmWanMbus3EValue2A		OBJECT-TYPE
			SYNTAX	INTEGER
			MAX-ACCESS	read-only
			STATUS	current
			::= { hmWanMbus3E 91 }

hmWanMbus3EVIF2B		OBJECT-TYPE
			SYNTAX	INTEGER
			MAX-ACCESS	read-only
			STATUS	current
			::= { hmWanMbus3E 92 }

hmWanMbus3EValue2B		OBJECT-TYPE
			SYNTAX	INTEGER
			MAX-ACCESS	read-only
			STATUS	current
			::= { hmWanMbus3E 93 }

hmWanMbus3EVIF2C		OBJECT-TYPE
			SYNTAX	INTEGER
			MAX-ACCESS	read-only
			STATUS	current
			::= { hmWanMbus3E 94 }

hmWanMbus3EValue2C		OBJECT-TYPE
			SYNTAX	INTEGER
			MAX-ACCESS	read-only
			STATUS	current
			::= { hmWanMbus3E 95 }

hmWanMbus3EVIF2D		OBJECT-TYPE
			SYNTAX	INTEGER
			MAX-ACCESS	read-only
			STATUS	current
			::= { hmWanMbus3E 96 }

hmWanMbus3EValue2D		OBJECT-TYPE
			SYNTAX	INTEGER
			MAX-ACCESS	read-only
			STATUS	current
			::= { hmWanMbus3E 97 }

hmWanMbus3EVIF2E		OBJECT-TYPE
			SYNTAX	INTEGER
			MAX-ACCESS	read-only
			STATUS	current
			::= { hmWanMbus3E 98 }

hmWanMbus3EValue2E		OBJECT-TYPE
			SYNTAX	INTEGER
			MAX-ACCESS	read-only
			STATUS	current
			::= { hmWanMbus3E 99 }

hmWanMbus3EVIF2F		OBJECT-TYPE
			SYNTAX	INTEGER
			MAX-ACCESS	read-only
			STATUS	current
			::= { hmWanMbus3E 100 }

hmWanMbus3EValue2F		OBJECT-TYPE
			SYNTAX	INTEGER
			MAX-ACCESS	read-only
			STATUS	current
			::= { hmWanMbus3E 101 }

hmWanMbus3F			OBJECT IDENTIFIER ::= { hmWanMbus 63 }

hmWanMbus3FIdNumber		OBJECT-TYPE
			SYNTAX	Gauge32
			MAX-ACCESS	read-only
			STATUS	current
			::= { hmWanMbus3F 1 }

hmWanMbus3FManufacturer	OBJECT-TYPE
			SYNTAX	Gauge32
			MAX-ACCESS	read-only
			STATUS	current
			::= { hmWanMbus3F 2 }

hmWanMbus3FVersion		OBJECT-TYPE
			SYNTAX	Gauge32
			MAX-ACCESS	read-only
			STATUS	current
			::= { hmWanMbus3F 3 }

hmWanMbus3FMedium		OBJECT-TYPE
			SYNTAX	Gauge32
			MAX-ACCESS	read-only
			STATUS	current
			::= { hmWanMbus3F 4 }

hmWanMbus3FStatus		OBJECT-TYPE
			SYNTAX	Gauge32
			MAX-ACCESS	read-only
			STATUS	current
			::= { hmWanMbus3F 5 }

hmWanMbus3FVIF00		OBJECT-TYPE
			SYNTAX	INTEGER
			MAX-ACCESS	read-only
			STATUS	current
			::= { hmWanMbus3F 6 }

hmWanMbus3FValue00		OBJECT-TYPE
			SYNTAX	INTEGER
			MAX-ACCESS	read-only
			STATUS	current
			::= { hmWanMbus3F 7 }

hmWanMbus3FVIF01		OBJECT-TYPE
			SYNTAX	INTEGER
			MAX-ACCESS	read-only
			STATUS	current
			::= { hmWanMbus3F 8 }

hmWanMbus3FValue01		OBJECT-TYPE
			SYNTAX	INTEGER
			MAX-ACCESS	read-only
			STATUS	current
			::= { hmWanMbus3F 9 }

hmWanMbus3FVIF02		OBJECT-TYPE
			SYNTAX	INTEGER
			MAX-ACCESS	read-only
			STATUS	current
			::= { hmWanMbus3F 10 }

hmWanMbus3FValue02		OBJECT-TYPE
			SYNTAX	INTEGER
			MAX-ACCESS	read-only
			STATUS	current
			::= { hmWanMbus3F 11 }

hmWanMbus3FVIF03		OBJECT-TYPE
			SYNTAX	INTEGER
			MAX-ACCESS	read-only
			STATUS	current
			::= { hmWanMbus3F 12 }

hmWanMbus3FValue03		OBJECT-TYPE
			SYNTAX	INTEGER
			MAX-ACCESS	read-only
			STATUS	current
			::= { hmWanMbus3F 13 }

hmWanMbus3FVIF04		OBJECT-TYPE
			SYNTAX	INTEGER
			MAX-ACCESS	read-only
			STATUS	current
			::= { hmWanMbus3F 14 }

hmWanMbus3FValue04		OBJECT-TYPE
			SYNTAX	INTEGER
			MAX-ACCESS	read-only
			STATUS	current
			::= { hmWanMbus3F 15 }

hmWanMbus3FVIF05		OBJECT-TYPE
			SYNTAX	INTEGER
			MAX-ACCESS	read-only
			STATUS	current
			::= { hmWanMbus3F 16 }

hmWanMbus3FValue05		OBJECT-TYPE
			SYNTAX	INTEGER
			MAX-ACCESS	read-only
			STATUS	current
			::= { hmWanMbus3F 17 }

hmWanMbus3FVIF06		OBJECT-TYPE
			SYNTAX	INTEGER
			MAX-ACCESS	read-only
			STATUS	current
			::= { hmWanMbus3F 18 }

hmWanMbus3FValue06		OBJECT-TYPE
			SYNTAX	INTEGER
			MAX-ACCESS	read-only
			STATUS	current
			::= { hmWanMbus3F 19 }

hmWanMbus3FVIF07		OBJECT-TYPE
			SYNTAX	INTEGER
			MAX-ACCESS	read-only
			STATUS	current
			::= { hmWanMbus3F 20 }

hmWanMbus3FValue07		OBJECT-TYPE
			SYNTAX	INTEGER
			MAX-ACCESS	read-only
			STATUS	current
			::= { hmWanMbus3F 21 }

hmWanMbus3FVIF08		OBJECT-TYPE
			SYNTAX	INTEGER
			MAX-ACCESS	read-only
			STATUS	current
			::= { hmWanMbus3F 22 }

hmWanMbus3FValue08		OBJECT-TYPE
			SYNTAX	INTEGER
			MAX-ACCESS	read-only
			STATUS	current
			::= { hmWanMbus3F 23 }

hmWanMbus3FVIF09		OBJECT-TYPE
			SYNTAX	INTEGER
			MAX-ACCESS	read-only
			STATUS	current
			::= { hmWanMbus3F 24 }

hmWanMbus3FValue09		OBJECT-TYPE
			SYNTAX	INTEGER
			MAX-ACCESS	read-only
			STATUS	current
			::= { hmWanMbus3F 25 }

hmWanMbus3FVIF0A		OBJECT-TYPE
			SYNTAX	INTEGER
			MAX-ACCESS	read-only
			STATUS	current
			::= { hmWanMbus3F 26 }

hmWanMbus3FValue0A		OBJECT-TYPE
			SYNTAX	INTEGER
			MAX-ACCESS	read-only
			STATUS	current
			::= { hmWanMbus3F 27 }

hmWanMbus3FVIF0B		OBJECT-TYPE
			SYNTAX	INTEGER
			MAX-ACCESS	read-only
			STATUS	current
			::= { hmWanMbus3F 28 }

hmWanMbus3FValue0B		OBJECT-TYPE
			SYNTAX	INTEGER
			MAX-ACCESS	read-only
			STATUS	current
			::= { hmWanMbus3F 29 }

hmWanMbus3FVIF0C		OBJECT-TYPE
			SYNTAX	INTEGER
			MAX-ACCESS	read-only
			STATUS	current
			::= { hmWanMbus3F 30 }

hmWanMbus3FValue0C		OBJECT-TYPE
			SYNTAX	INTEGER
			MAX-ACCESS	read-only
			STATUS	current
			::= { hmWanMbus3F 31 }

hmWanMbus3FVIF0D		OBJECT-TYPE
			SYNTAX	INTEGER
			MAX-ACCESS	read-only
			STATUS	current
			::= { hmWanMbus3F 32 }

hmWanMbus3FValue0D		OBJECT-TYPE
			SYNTAX	INTEGER
			MAX-ACCESS	read-only
			STATUS	current
			::= { hmWanMbus3F 33 }

hmWanMbus3FVIF0E		OBJECT-TYPE
			SYNTAX	INTEGER
			MAX-ACCESS	read-only
			STATUS	current
			::= { hmWanMbus3F 34 }

hmWanMbus3FValue0E		OBJECT-TYPE
			SYNTAX	INTEGER
			MAX-ACCESS	read-only
			STATUS	current
			::= { hmWanMbus3F 35 }

hmWanMbus3FVIF0F		OBJECT-TYPE
			SYNTAX	INTEGER
			MAX-ACCESS	read-only
			STATUS	current
			::= { hmWanMbus3F 36 }

hmWanMbus3FValue0F		OBJECT-TYPE
			SYNTAX	INTEGER
			MAX-ACCESS	read-only
			STATUS	current
			::= { hmWanMbus3F 37 }

hmWanMbus3FVIF10		OBJECT-TYPE
			SYNTAX	INTEGER
			MAX-ACCESS	read-only
			STATUS	current
			::= { hmWanMbus3F 38 }

hmWanMbus3FValue10		OBJECT-TYPE
			SYNTAX	INTEGER
			MAX-ACCESS	read-only
			STATUS	current
			::= { hmWanMbus3F 39 }

hmWanMbus3FVIF11		OBJECT-TYPE
			SYNTAX	INTEGER
			MAX-ACCESS	read-only
			STATUS	current
			::= { hmWanMbus3F 40 }

hmWanMbus3FValue11		OBJECT-TYPE
			SYNTAX	INTEGER
			MAX-ACCESS	read-only
			STATUS	current
			::= { hmWanMbus3F 41 }

hmWanMbus3FVIF12		OBJECT-TYPE
			SYNTAX	INTEGER
			MAX-ACCESS	read-only
			STATUS	current
			::= { hmWanMbus3F 42 }

hmWanMbus3FValue12		OBJECT-TYPE
			SYNTAX	INTEGER
			MAX-ACCESS	read-only
			STATUS	current
			::= { hmWanMbus3F 43 }

hmWanMbus3FVIF13		OBJECT-TYPE
			SYNTAX	INTEGER
			MAX-ACCESS	read-only
			STATUS	current
			::= { hmWanMbus3F 44 }

hmWanMbus3FValue13		OBJECT-TYPE
			SYNTAX	INTEGER
			MAX-ACCESS	read-only
			STATUS	current
			::= { hmWanMbus3F 45 }

hmWanMbus3FVIF14		OBJECT-TYPE
			SYNTAX	INTEGER
			MAX-ACCESS	read-only
			STATUS	current
			::= { hmWanMbus3F 46 }

hmWanMbus3FValue14		OBJECT-TYPE
			SYNTAX	INTEGER
			MAX-ACCESS	read-only
			STATUS	current
			::= { hmWanMbus3F 47 }

hmWanMbus3FVIF15		OBJECT-TYPE
			SYNTAX	INTEGER
			MAX-ACCESS	read-only
			STATUS	current
			::= { hmWanMbus3F 48 }

hmWanMbus3FValue15		OBJECT-TYPE
			SYNTAX	INTEGER
			MAX-ACCESS	read-only
			STATUS	current
			::= { hmWanMbus3F 49 }

hmWanMbus3FVIF16		OBJECT-TYPE
			SYNTAX	INTEGER
			MAX-ACCESS	read-only
			STATUS	current
			::= { hmWanMbus3F 50 }

hmWanMbus3FValue16		OBJECT-TYPE
			SYNTAX	INTEGER
			MAX-ACCESS	read-only
			STATUS	current
			::= { hmWanMbus3F 51 }

hmWanMbus3FVIF17		OBJECT-TYPE
			SYNTAX	INTEGER
			MAX-ACCESS	read-only
			STATUS	current
			::= { hmWanMbus3F 52 }

hmWanMbus3FValue17		OBJECT-TYPE
			SYNTAX	INTEGER
			MAX-ACCESS	read-only
			STATUS	current
			::= { hmWanMbus3F 53 }

hmWanMbus3FVIF18		OBJECT-TYPE
			SYNTAX	INTEGER
			MAX-ACCESS	read-only
			STATUS	current
			::= { hmWanMbus3F 54 }

hmWanMbus3FValue18		OBJECT-TYPE
			SYNTAX	INTEGER
			MAX-ACCESS	read-only
			STATUS	current
			::= { hmWanMbus3F 55 }

hmWanMbus3FVIF19		OBJECT-TYPE
			SYNTAX	INTEGER
			MAX-ACCESS	read-only
			STATUS	current
			::= { hmWanMbus3F 56 }

hmWanMbus3FValue19		OBJECT-TYPE
			SYNTAX	INTEGER
			MAX-ACCESS	read-only
			STATUS	current
			::= { hmWanMbus3F 57 }

hmWanMbus3FVIF1A		OBJECT-TYPE
			SYNTAX	INTEGER
			MAX-ACCESS	read-only
			STATUS	current
			::= { hmWanMbus3F 58 }

hmWanMbus3FValue1A		OBJECT-TYPE
			SYNTAX	INTEGER
			MAX-ACCESS	read-only
			STATUS	current
			::= { hmWanMbus3F 59 }

hmWanMbus3FVIF1B		OBJECT-TYPE
			SYNTAX	INTEGER
			MAX-ACCESS	read-only
			STATUS	current
			::= { hmWanMbus3F 60 }

hmWanMbus3FValue1B		OBJECT-TYPE
			SYNTAX	INTEGER
			MAX-ACCESS	read-only
			STATUS	current
			::= { hmWanMbus3F 61 }

hmWanMbus3FVIF1C		OBJECT-TYPE
			SYNTAX	INTEGER
			MAX-ACCESS	read-only
			STATUS	current
			::= { hmWanMbus3F 62 }

hmWanMbus3FValue1C		OBJECT-TYPE
			SYNTAX	INTEGER
			MAX-ACCESS	read-only
			STATUS	current
			::= { hmWanMbus3F 63 }

hmWanMbus3FVIF1D		OBJECT-TYPE
			SYNTAX	INTEGER
			MAX-ACCESS	read-only
			STATUS	current
			::= { hmWanMbus3F 64 }

hmWanMbus3FValue1D		OBJECT-TYPE
			SYNTAX	INTEGER
			MAX-ACCESS	read-only
			STATUS	current
			::= { hmWanMbus3F 65 }

hmWanMbus3FVIF1E		OBJECT-TYPE
			SYNTAX	INTEGER
			MAX-ACCESS	read-only
			STATUS	current
			::= { hmWanMbus3F 66 }

hmWanMbus3FValue1E		OBJECT-TYPE
			SYNTAX	INTEGER
			MAX-ACCESS	read-only
			STATUS	current
			::= { hmWanMbus3F 67 }

hmWanMbus3FVIF1F		OBJECT-TYPE
			SYNTAX	INTEGER
			MAX-ACCESS	read-only
			STATUS	current
			::= { hmWanMbus3F 68 }

hmWanMbus3FValue1F		OBJECT-TYPE
			SYNTAX	INTEGER
			MAX-ACCESS	read-only
			STATUS	current
			::= { hmWanMbus3F 69 }

hmWanMbus3FVIF20		OBJECT-TYPE
			SYNTAX	INTEGER
			MAX-ACCESS	read-only
			STATUS	current
			::= { hmWanMbus3F 70 }

hmWanMbus3FValue20		OBJECT-TYPE
			SYNTAX	INTEGER
			MAX-ACCESS	read-only
			STATUS	current
			::= { hmWanMbus3F 71 }

hmWanMbus3FVIF21		OBJECT-TYPE
			SYNTAX	INTEGER
			MAX-ACCESS	read-only
			STATUS	current
			::= { hmWanMbus3F 72 }

hmWanMbus3FValue21		OBJECT-TYPE
			SYNTAX	INTEGER
			MAX-ACCESS	read-only
			STATUS	current
			::= { hmWanMbus3F 73 }

hmWanMbus3FVIF22		OBJECT-TYPE
			SYNTAX	INTEGER
			MAX-ACCESS	read-only
			STATUS	current
			::= { hmWanMbus3F 74 }

hmWanMbus3FValue22		OBJECT-TYPE
			SYNTAX	INTEGER
			MAX-ACCESS	read-only
			STATUS	current
			::= { hmWanMbus3F 75 }

hmWanMbus3FVIF23		OBJECT-TYPE
			SYNTAX	INTEGER
			MAX-ACCESS	read-only
			STATUS	current
			::= { hmWanMbus3F 76 }

hmWanMbus3FValue23		OBJECT-TYPE
			SYNTAX	INTEGER
			MAX-ACCESS	read-only
			STATUS	current
			::= { hmWanMbus3F 77 }

hmWanMbus3FVIF24		OBJECT-TYPE
			SYNTAX	INTEGER
			MAX-ACCESS	read-only
			STATUS	current
			::= { hmWanMbus3F 78 }

hmWanMbus3FValue24		OBJECT-TYPE
			SYNTAX	INTEGER
			MAX-ACCESS	read-only
			STATUS	current
			::= { hmWanMbus3F 79 }

hmWanMbus3FVIF25		OBJECT-TYPE
			SYNTAX	INTEGER
			MAX-ACCESS	read-only
			STATUS	current
			::= { hmWanMbus3F 80 }

hmWanMbus3FValue25		OBJECT-TYPE
			SYNTAX	INTEGER
			MAX-ACCESS	read-only
			STATUS	current
			::= { hmWanMbus3F 81 }

hmWanMbus3FVIF26		OBJECT-TYPE
			SYNTAX	INTEGER
			MAX-ACCESS	read-only
			STATUS	current
			::= { hmWanMbus3F 82 }

hmWanMbus3FValue26		OBJECT-TYPE
			SYNTAX	INTEGER
			MAX-ACCESS	read-only
			STATUS	current
			::= { hmWanMbus3F 83 }

hmWanMbus3FVIF27		OBJECT-TYPE
			SYNTAX	INTEGER
			MAX-ACCESS	read-only
			STATUS	current
			::= { hmWanMbus3F 84 }

hmWanMbus3FValue27		OBJECT-TYPE
			SYNTAX	INTEGER
			MAX-ACCESS	read-only
			STATUS	current
			::= { hmWanMbus3F 85 }

hmWanMbus3FVIF28		OBJECT-TYPE
			SYNTAX	INTEGER
			MAX-ACCESS	read-only
			STATUS	current
			::= { hmWanMbus3F 86 }

hmWanMbus3FValue28		OBJECT-TYPE
			SYNTAX	INTEGER
			MAX-ACCESS	read-only
			STATUS	current
			::= { hmWanMbus3F 87 }

hmWanMbus3FVIF29		OBJECT-TYPE
			SYNTAX	INTEGER
			MAX-ACCESS	read-only
			STATUS	current
			::= { hmWanMbus3F 88 }

hmWanMbus3FValue29		OBJECT-TYPE
			SYNTAX	INTEGER
			MAX-ACCESS	read-only
			STATUS	current
			::= { hmWanMbus3F 89 }

hmWanMbus3FVIF2A		OBJECT-TYPE
			SYNTAX	INTEGER
			MAX-ACCESS	read-only
			STATUS	current
			::= { hmWanMbus3F 90 }

hmWanMbus3FValue2A		OBJECT-TYPE
			SYNTAX	INTEGER
			MAX-ACCESS	read-only
			STATUS	current
			::= { hmWanMbus3F 91 }

hmWanMbus3FVIF2B		OBJECT-TYPE
			SYNTAX	INTEGER
			MAX-ACCESS	read-only
			STATUS	current
			::= { hmWanMbus3F 92 }

hmWanMbus3FValue2B		OBJECT-TYPE
			SYNTAX	INTEGER
			MAX-ACCESS	read-only
			STATUS	current
			::= { hmWanMbus3F 93 }

hmWanMbus3FVIF2C		OBJECT-TYPE
			SYNTAX	INTEGER
			MAX-ACCESS	read-only
			STATUS	current
			::= { hmWanMbus3F 94 }

hmWanMbus3FValue2C		OBJECT-TYPE
			SYNTAX	INTEGER
			MAX-ACCESS	read-only
			STATUS	current
			::= { hmWanMbus3F 95 }

hmWanMbus3FVIF2D		OBJECT-TYPE
			SYNTAX	INTEGER
			MAX-ACCESS	read-only
			STATUS	current
			::= { hmWanMbus3F 96 }

hmWanMbus3FValue2D		OBJECT-TYPE
			SYNTAX	INTEGER
			MAX-ACCESS	read-only
			STATUS	current
			::= { hmWanMbus3F 97 }

hmWanMbus3FVIF2E		OBJECT-TYPE
			SYNTAX	INTEGER
			MAX-ACCESS	read-only
			STATUS	current
			::= { hmWanMbus3F 98 }

hmWanMbus3FValue2E		OBJECT-TYPE
			SYNTAX	INTEGER
			MAX-ACCESS	read-only
			STATUS	current
			::= { hmWanMbus3F 99 }

hmWanMbus3FVIF2F		OBJECT-TYPE
			SYNTAX	INTEGER
			MAX-ACCESS	read-only
			STATUS	current
			::= { hmWanMbus3F 100 }

hmWanMbus3FValue2F		OBJECT-TYPE
			SYNTAX	INTEGER
			MAX-ACCESS	read-only
			STATUS	current
			::= { hmWanMbus3F 101 }

hmWanMbus40			OBJECT IDENTIFIER ::= { hmWanMbus 64 }

hmWanMbus40IdNumber		OBJECT-TYPE
			SYNTAX	Gauge32
			MAX-ACCESS	read-only
			STATUS	current
			::= { hmWanMbus40 1 }

hmWanMbus40Manufacturer	OBJECT-TYPE
			SYNTAX	Gauge32
			MAX-ACCESS	read-only
			STATUS	current
			::= { hmWanMbus40 2 }

hmWanMbus40Version		OBJECT-TYPE
			SYNTAX	Gauge32
			MAX-ACCESS	read-only
			STATUS	current
			::= { hmWanMbus40 3 }

hmWanMbus40Medium		OBJECT-TYPE
			SYNTAX	Gauge32
			MAX-ACCESS	read-only
			STATUS	current
			::= { hmWanMbus40 4 }

hmWanMbus40Status		OBJECT-TYPE
			SYNTAX	Gauge32
			MAX-ACCESS	read-only
			STATUS	current
			::= { hmWanMbus40 5 }

hmWanMbus40VIF00		OBJECT-TYPE
			SYNTAX	INTEGER
			MAX-ACCESS	read-only
			STATUS	current
			::= { hmWanMbus40 6 }

hmWanMbus40Value00		OBJECT-TYPE
			SYNTAX	INTEGER
			MAX-ACCESS	read-only
			STATUS	current
			::= { hmWanMbus40 7 }

hmWanMbus40VIF01		OBJECT-TYPE
			SYNTAX	INTEGER
			MAX-ACCESS	read-only
			STATUS	current
			::= { hmWanMbus40 8 }

hmWanMbus40Value01		OBJECT-TYPE
			SYNTAX	INTEGER
			MAX-ACCESS	read-only
			STATUS	current
			::= { hmWanMbus40 9 }

hmWanMbus40VIF02		OBJECT-TYPE
			SYNTAX	INTEGER
			MAX-ACCESS	read-only
			STATUS	current
			::= { hmWanMbus40 10 }

hmWanMbus40Value02		OBJECT-TYPE
			SYNTAX	INTEGER
			MAX-ACCESS	read-only
			STATUS	current
			::= { hmWanMbus40 11 }

hmWanMbus40VIF03		OBJECT-TYPE
			SYNTAX	INTEGER
			MAX-ACCESS	read-only
			STATUS	current
			::= { hmWanMbus40 12 }

hmWanMbus40Value03		OBJECT-TYPE
			SYNTAX	INTEGER
			MAX-ACCESS	read-only
			STATUS	current
			::= { hmWanMbus40 13 }

hmWanMbus40VIF04		OBJECT-TYPE
			SYNTAX	INTEGER
			MAX-ACCESS	read-only
			STATUS	current
			::= { hmWanMbus40 14 }

hmWanMbus40Value04		OBJECT-TYPE
			SYNTAX	INTEGER
			MAX-ACCESS	read-only
			STATUS	current
			::= { hmWanMbus40 15 }

hmWanMbus40VIF05		OBJECT-TYPE
			SYNTAX	INTEGER
			MAX-ACCESS	read-only
			STATUS	current
			::= { hmWanMbus40 16 }

hmWanMbus40Value05		OBJECT-TYPE
			SYNTAX	INTEGER
			MAX-ACCESS	read-only
			STATUS	current
			::= { hmWanMbus40 17 }

hmWanMbus40VIF06		OBJECT-TYPE
			SYNTAX	INTEGER
			MAX-ACCESS	read-only
			STATUS	current
			::= { hmWanMbus40 18 }

hmWanMbus40Value06		OBJECT-TYPE
			SYNTAX	INTEGER
			MAX-ACCESS	read-only
			STATUS	current
			::= { hmWanMbus40 19 }

hmWanMbus40VIF07		OBJECT-TYPE
			SYNTAX	INTEGER
			MAX-ACCESS	read-only
			STATUS	current
			::= { hmWanMbus40 20 }

hmWanMbus40Value07		OBJECT-TYPE
			SYNTAX	INTEGER
			MAX-ACCESS	read-only
			STATUS	current
			::= { hmWanMbus40 21 }

hmWanMbus40VIF08		OBJECT-TYPE
			SYNTAX	INTEGER
			MAX-ACCESS	read-only
			STATUS	current
			::= { hmWanMbus40 22 }

hmWanMbus40Value08		OBJECT-TYPE
			SYNTAX	INTEGER
			MAX-ACCESS	read-only
			STATUS	current
			::= { hmWanMbus40 23 }

hmWanMbus40VIF09		OBJECT-TYPE
			SYNTAX	INTEGER
			MAX-ACCESS	read-only
			STATUS	current
			::= { hmWanMbus40 24 }

hmWanMbus40Value09		OBJECT-TYPE
			SYNTAX	INTEGER
			MAX-ACCESS	read-only
			STATUS	current
			::= { hmWanMbus40 25 }

hmWanMbus40VIF0A		OBJECT-TYPE
			SYNTAX	INTEGER
			MAX-ACCESS	read-only
			STATUS	current
			::= { hmWanMbus40 26 }

hmWanMbus40Value0A		OBJECT-TYPE
			SYNTAX	INTEGER
			MAX-ACCESS	read-only
			STATUS	current
			::= { hmWanMbus40 27 }

hmWanMbus40VIF0B		OBJECT-TYPE
			SYNTAX	INTEGER
			MAX-ACCESS	read-only
			STATUS	current
			::= { hmWanMbus40 28 }

hmWanMbus40Value0B		OBJECT-TYPE
			SYNTAX	INTEGER
			MAX-ACCESS	read-only
			STATUS	current
			::= { hmWanMbus40 29 }

hmWanMbus40VIF0C		OBJECT-TYPE
			SYNTAX	INTEGER
			MAX-ACCESS	read-only
			STATUS	current
			::= { hmWanMbus40 30 }

hmWanMbus40Value0C		OBJECT-TYPE
			SYNTAX	INTEGER
			MAX-ACCESS	read-only
			STATUS	current
			::= { hmWanMbus40 31 }

hmWanMbus40VIF0D		OBJECT-TYPE
			SYNTAX	INTEGER
			MAX-ACCESS	read-only
			STATUS	current
			::= { hmWanMbus40 32 }

hmWanMbus40Value0D		OBJECT-TYPE
			SYNTAX	INTEGER
			MAX-ACCESS	read-only
			STATUS	current
			::= { hmWanMbus40 33 }

hmWanMbus40VIF0E		OBJECT-TYPE
			SYNTAX	INTEGER
			MAX-ACCESS	read-only
			STATUS	current
			::= { hmWanMbus40 34 }

hmWanMbus40Value0E		OBJECT-TYPE
			SYNTAX	INTEGER
			MAX-ACCESS	read-only
			STATUS	current
			::= { hmWanMbus40 35 }

hmWanMbus40VIF0F		OBJECT-TYPE
			SYNTAX	INTEGER
			MAX-ACCESS	read-only
			STATUS	current
			::= { hmWanMbus40 36 }

hmWanMbus40Value0F		OBJECT-TYPE
			SYNTAX	INTEGER
			MAX-ACCESS	read-only
			STATUS	current
			::= { hmWanMbus40 37 }

hmWanMbus40VIF10		OBJECT-TYPE
			SYNTAX	INTEGER
			MAX-ACCESS	read-only
			STATUS	current
			::= { hmWanMbus40 38 }

hmWanMbus40Value10		OBJECT-TYPE
			SYNTAX	INTEGER
			MAX-ACCESS	read-only
			STATUS	current
			::= { hmWanMbus40 39 }

hmWanMbus40VIF11		OBJECT-TYPE
			SYNTAX	INTEGER
			MAX-ACCESS	read-only
			STATUS	current
			::= { hmWanMbus40 40 }

hmWanMbus40Value11		OBJECT-TYPE
			SYNTAX	INTEGER
			MAX-ACCESS	read-only
			STATUS	current
			::= { hmWanMbus40 41 }

hmWanMbus40VIF12		OBJECT-TYPE
			SYNTAX	INTEGER
			MAX-ACCESS	read-only
			STATUS	current
			::= { hmWanMbus40 42 }

hmWanMbus40Value12		OBJECT-TYPE
			SYNTAX	INTEGER
			MAX-ACCESS	read-only
			STATUS	current
			::= { hmWanMbus40 43 }

hmWanMbus40VIF13		OBJECT-TYPE
			SYNTAX	INTEGER
			MAX-ACCESS	read-only
			STATUS	current
			::= { hmWanMbus40 44 }

hmWanMbus40Value13		OBJECT-TYPE
			SYNTAX	INTEGER
			MAX-ACCESS	read-only
			STATUS	current
			::= { hmWanMbus40 45 }

hmWanMbus40VIF14		OBJECT-TYPE
			SYNTAX	INTEGER
			MAX-ACCESS	read-only
			STATUS	current
			::= { hmWanMbus40 46 }

hmWanMbus40Value14		OBJECT-TYPE
			SYNTAX	INTEGER
			MAX-ACCESS	read-only
			STATUS	current
			::= { hmWanMbus40 47 }

hmWanMbus40VIF15		OBJECT-TYPE
			SYNTAX	INTEGER
			MAX-ACCESS	read-only
			STATUS	current
			::= { hmWanMbus40 48 }

hmWanMbus40Value15		OBJECT-TYPE
			SYNTAX	INTEGER
			MAX-ACCESS	read-only
			STATUS	current
			::= { hmWanMbus40 49 }

hmWanMbus40VIF16		OBJECT-TYPE
			SYNTAX	INTEGER
			MAX-ACCESS	read-only
			STATUS	current
			::= { hmWanMbus40 50 }

hmWanMbus40Value16		OBJECT-TYPE
			SYNTAX	INTEGER
			MAX-ACCESS	read-only
			STATUS	current
			::= { hmWanMbus40 51 }

hmWanMbus40VIF17		OBJECT-TYPE
			SYNTAX	INTEGER
			MAX-ACCESS	read-only
			STATUS	current
			::= { hmWanMbus40 52 }

hmWanMbus40Value17		OBJECT-TYPE
			SYNTAX	INTEGER
			MAX-ACCESS	read-only
			STATUS	current
			::= { hmWanMbus40 53 }

hmWanMbus40VIF18		OBJECT-TYPE
			SYNTAX	INTEGER
			MAX-ACCESS	read-only
			STATUS	current
			::= { hmWanMbus40 54 }

hmWanMbus40Value18		OBJECT-TYPE
			SYNTAX	INTEGER
			MAX-ACCESS	read-only
			STATUS	current
			::= { hmWanMbus40 55 }

hmWanMbus40VIF19		OBJECT-TYPE
			SYNTAX	INTEGER
			MAX-ACCESS	read-only
			STATUS	current
			::= { hmWanMbus40 56 }

hmWanMbus40Value19		OBJECT-TYPE
			SYNTAX	INTEGER
			MAX-ACCESS	read-only
			STATUS	current
			::= { hmWanMbus40 57 }

hmWanMbus40VIF1A		OBJECT-TYPE
			SYNTAX	INTEGER
			MAX-ACCESS	read-only
			STATUS	current
			::= { hmWanMbus40 58 }

hmWanMbus40Value1A		OBJECT-TYPE
			SYNTAX	INTEGER
			MAX-ACCESS	read-only
			STATUS	current
			::= { hmWanMbus40 59 }

hmWanMbus40VIF1B		OBJECT-TYPE
			SYNTAX	INTEGER
			MAX-ACCESS	read-only
			STATUS	current
			::= { hmWanMbus40 60 }

hmWanMbus40Value1B		OBJECT-TYPE
			SYNTAX	INTEGER
			MAX-ACCESS	read-only
			STATUS	current
			::= { hmWanMbus40 61 }

hmWanMbus40VIF1C		OBJECT-TYPE
			SYNTAX	INTEGER
			MAX-ACCESS	read-only
			STATUS	current
			::= { hmWanMbus40 62 }

hmWanMbus40Value1C		OBJECT-TYPE
			SYNTAX	INTEGER
			MAX-ACCESS	read-only
			STATUS	current
			::= { hmWanMbus40 63 }

hmWanMbus40VIF1D		OBJECT-TYPE
			SYNTAX	INTEGER
			MAX-ACCESS	read-only
			STATUS	current
			::= { hmWanMbus40 64 }

hmWanMbus40Value1D		OBJECT-TYPE
			SYNTAX	INTEGER
			MAX-ACCESS	read-only
			STATUS	current
			::= { hmWanMbus40 65 }

hmWanMbus40VIF1E		OBJECT-TYPE
			SYNTAX	INTEGER
			MAX-ACCESS	read-only
			STATUS	current
			::= { hmWanMbus40 66 }

hmWanMbus40Value1E		OBJECT-TYPE
			SYNTAX	INTEGER
			MAX-ACCESS	read-only
			STATUS	current
			::= { hmWanMbus40 67 }

hmWanMbus40VIF1F		OBJECT-TYPE
			SYNTAX	INTEGER
			MAX-ACCESS	read-only
			STATUS	current
			::= { hmWanMbus40 68 }

hmWanMbus40Value1F		OBJECT-TYPE
			SYNTAX	INTEGER
			MAX-ACCESS	read-only
			STATUS	current
			::= { hmWanMbus40 69 }

hmWanMbus40VIF20		OBJECT-TYPE
			SYNTAX	INTEGER
			MAX-ACCESS	read-only
			STATUS	current
			::= { hmWanMbus40 70 }

hmWanMbus40Value20		OBJECT-TYPE
			SYNTAX	INTEGER
			MAX-ACCESS	read-only
			STATUS	current
			::= { hmWanMbus40 71 }

hmWanMbus40VIF21		OBJECT-TYPE
			SYNTAX	INTEGER
			MAX-ACCESS	read-only
			STATUS	current
			::= { hmWanMbus40 72 }

hmWanMbus40Value21		OBJECT-TYPE
			SYNTAX	INTEGER
			MAX-ACCESS	read-only
			STATUS	current
			::= { hmWanMbus40 73 }

hmWanMbus40VIF22		OBJECT-TYPE
			SYNTAX	INTEGER
			MAX-ACCESS	read-only
			STATUS	current
			::= { hmWanMbus40 74 }

hmWanMbus40Value22		OBJECT-TYPE
			SYNTAX	INTEGER
			MAX-ACCESS	read-only
			STATUS	current
			::= { hmWanMbus40 75 }

hmWanMbus40VIF23		OBJECT-TYPE
			SYNTAX	INTEGER
			MAX-ACCESS	read-only
			STATUS	current
			::= { hmWanMbus40 76 }

hmWanMbus40Value23		OBJECT-TYPE
			SYNTAX	INTEGER
			MAX-ACCESS	read-only
			STATUS	current
			::= { hmWanMbus40 77 }

hmWanMbus40VIF24		OBJECT-TYPE
			SYNTAX	INTEGER
			MAX-ACCESS	read-only
			STATUS	current
			::= { hmWanMbus40 78 }

hmWanMbus40Value24		OBJECT-TYPE
			SYNTAX	INTEGER
			MAX-ACCESS	read-only
			STATUS	current
			::= { hmWanMbus40 79 }

hmWanMbus40VIF25		OBJECT-TYPE
			SYNTAX	INTEGER
			MAX-ACCESS	read-only
			STATUS	current
			::= { hmWanMbus40 80 }

hmWanMbus40Value25		OBJECT-TYPE
			SYNTAX	INTEGER
			MAX-ACCESS	read-only
			STATUS	current
			::= { hmWanMbus40 81 }

hmWanMbus40VIF26		OBJECT-TYPE
			SYNTAX	INTEGER
			MAX-ACCESS	read-only
			STATUS	current
			::= { hmWanMbus40 82 }

hmWanMbus40Value26		OBJECT-TYPE
			SYNTAX	INTEGER
			MAX-ACCESS	read-only
			STATUS	current
			::= { hmWanMbus40 83 }

hmWanMbus40VIF27		OBJECT-TYPE
			SYNTAX	INTEGER
			MAX-ACCESS	read-only
			STATUS	current
			::= { hmWanMbus40 84 }

hmWanMbus40Value27		OBJECT-TYPE
			SYNTAX	INTEGER
			MAX-ACCESS	read-only
			STATUS	current
			::= { hmWanMbus40 85 }

hmWanMbus40VIF28		OBJECT-TYPE
			SYNTAX	INTEGER
			MAX-ACCESS	read-only
			STATUS	current
			::= { hmWanMbus40 86 }

hmWanMbus40Value28		OBJECT-TYPE
			SYNTAX	INTEGER
			MAX-ACCESS	read-only
			STATUS	current
			::= { hmWanMbus40 87 }

hmWanMbus40VIF29		OBJECT-TYPE
			SYNTAX	INTEGER
			MAX-ACCESS	read-only
			STATUS	current
			::= { hmWanMbus40 88 }

hmWanMbus40Value29		OBJECT-TYPE
			SYNTAX	INTEGER
			MAX-ACCESS	read-only
			STATUS	current
			::= { hmWanMbus40 89 }

hmWanMbus40VIF2A		OBJECT-TYPE
			SYNTAX	INTEGER
			MAX-ACCESS	read-only
			STATUS	current
			::= { hmWanMbus40 90 }

hmWanMbus40Value2A		OBJECT-TYPE
			SYNTAX	INTEGER
			MAX-ACCESS	read-only
			STATUS	current
			::= { hmWanMbus40 91 }

hmWanMbus40VIF2B		OBJECT-TYPE
			SYNTAX	INTEGER
			MAX-ACCESS	read-only
			STATUS	current
			::= { hmWanMbus40 92 }

hmWanMbus40Value2B		OBJECT-TYPE
			SYNTAX	INTEGER
			MAX-ACCESS	read-only
			STATUS	current
			::= { hmWanMbus40 93 }

hmWanMbus40VIF2C		OBJECT-TYPE
			SYNTAX	INTEGER
			MAX-ACCESS	read-only
			STATUS	current
			::= { hmWanMbus40 94 }

hmWanMbus40Value2C		OBJECT-TYPE
			SYNTAX	INTEGER
			MAX-ACCESS	read-only
			STATUS	current
			::= { hmWanMbus40 95 }

hmWanMbus40VIF2D		OBJECT-TYPE
			SYNTAX	INTEGER
			MAX-ACCESS	read-only
			STATUS	current
			::= { hmWanMbus40 96 }

hmWanMbus40Value2D		OBJECT-TYPE
			SYNTAX	INTEGER
			MAX-ACCESS	read-only
			STATUS	current
			::= { hmWanMbus40 97 }

hmWanMbus40VIF2E		OBJECT-TYPE
			SYNTAX	INTEGER
			MAX-ACCESS	read-only
			STATUS	current
			::= { hmWanMbus40 98 }

hmWanMbus40Value2E		OBJECT-TYPE
			SYNTAX	INTEGER
			MAX-ACCESS	read-only
			STATUS	current
			::= { hmWanMbus40 99 }

hmWanMbus40VIF2F		OBJECT-TYPE
			SYNTAX	INTEGER
			MAX-ACCESS	read-only
			STATUS	current
			::= { hmWanMbus40 100 }

hmWanMbus40Value2F		OBJECT-TYPE
			SYNTAX	INTEGER
			MAX-ACCESS	read-only
			STATUS	current
			::= { hmWanMbus40 101 }

hmWanMbus41			OBJECT IDENTIFIER ::= { hmWanMbus 65 }

hmWanMbus41IdNumber		OBJECT-TYPE
			SYNTAX	Gauge32
			MAX-ACCESS	read-only
			STATUS	current
			::= { hmWanMbus41 1 }

hmWanMbus41Manufacturer	OBJECT-TYPE
			SYNTAX	Gauge32
			MAX-ACCESS	read-only
			STATUS	current
			::= { hmWanMbus41 2 }

hmWanMbus41Version		OBJECT-TYPE
			SYNTAX	Gauge32
			MAX-ACCESS	read-only
			STATUS	current
			::= { hmWanMbus41 3 }

hmWanMbus41Medium		OBJECT-TYPE
			SYNTAX	Gauge32
			MAX-ACCESS	read-only
			STATUS	current
			::= { hmWanMbus41 4 }

hmWanMbus41Status		OBJECT-TYPE
			SYNTAX	Gauge32
			MAX-ACCESS	read-only
			STATUS	current
			::= { hmWanMbus41 5 }

hmWanMbus41VIF00		OBJECT-TYPE
			SYNTAX	INTEGER
			MAX-ACCESS	read-only
			STATUS	current
			::= { hmWanMbus41 6 }

hmWanMbus41Value00		OBJECT-TYPE
			SYNTAX	INTEGER
			MAX-ACCESS	read-only
			STATUS	current
			::= { hmWanMbus41 7 }

hmWanMbus41VIF01		OBJECT-TYPE
			SYNTAX	INTEGER
			MAX-ACCESS	read-only
			STATUS	current
			::= { hmWanMbus41 8 }

hmWanMbus41Value01		OBJECT-TYPE
			SYNTAX	INTEGER
			MAX-ACCESS	read-only
			STATUS	current
			::= { hmWanMbus41 9 }

hmWanMbus41VIF02		OBJECT-TYPE
			SYNTAX	INTEGER
			MAX-ACCESS	read-only
			STATUS	current
			::= { hmWanMbus41 10 }

hmWanMbus41Value02		OBJECT-TYPE
			SYNTAX	INTEGER
			MAX-ACCESS	read-only
			STATUS	current
			::= { hmWanMbus41 11 }

hmWanMbus41VIF03		OBJECT-TYPE
			SYNTAX	INTEGER
			MAX-ACCESS	read-only
			STATUS	current
			::= { hmWanMbus41 12 }

hmWanMbus41Value03		OBJECT-TYPE
			SYNTAX	INTEGER
			MAX-ACCESS	read-only
			STATUS	current
			::= { hmWanMbus41 13 }

hmWanMbus41VIF04		OBJECT-TYPE
			SYNTAX	INTEGER
			MAX-ACCESS	read-only
			STATUS	current
			::= { hmWanMbus41 14 }

hmWanMbus41Value04		OBJECT-TYPE
			SYNTAX	INTEGER
			MAX-ACCESS	read-only
			STATUS	current
			::= { hmWanMbus41 15 }

hmWanMbus41VIF05		OBJECT-TYPE
			SYNTAX	INTEGER
			MAX-ACCESS	read-only
			STATUS	current
			::= { hmWanMbus41 16 }

hmWanMbus41Value05		OBJECT-TYPE
			SYNTAX	INTEGER
			MAX-ACCESS	read-only
			STATUS	current
			::= { hmWanMbus41 17 }

hmWanMbus41VIF06		OBJECT-TYPE
			SYNTAX	INTEGER
			MAX-ACCESS	read-only
			STATUS	current
			::= { hmWanMbus41 18 }

hmWanMbus41Value06		OBJECT-TYPE
			SYNTAX	INTEGER
			MAX-ACCESS	read-only
			STATUS	current
			::= { hmWanMbus41 19 }

hmWanMbus41VIF07		OBJECT-TYPE
			SYNTAX	INTEGER
			MAX-ACCESS	read-only
			STATUS	current
			::= { hmWanMbus41 20 }

hmWanMbus41Value07		OBJECT-TYPE
			SYNTAX	INTEGER
			MAX-ACCESS	read-only
			STATUS	current
			::= { hmWanMbus41 21 }

hmWanMbus41VIF08		OBJECT-TYPE
			SYNTAX	INTEGER
			MAX-ACCESS	read-only
			STATUS	current
			::= { hmWanMbus41 22 }

hmWanMbus41Value08		OBJECT-TYPE
			SYNTAX	INTEGER
			MAX-ACCESS	read-only
			STATUS	current
			::= { hmWanMbus41 23 }

hmWanMbus41VIF09		OBJECT-TYPE
			SYNTAX	INTEGER
			MAX-ACCESS	read-only
			STATUS	current
			::= { hmWanMbus41 24 }

hmWanMbus41Value09		OBJECT-TYPE
			SYNTAX	INTEGER
			MAX-ACCESS	read-only
			STATUS	current
			::= { hmWanMbus41 25 }

hmWanMbus41VIF0A		OBJECT-TYPE
			SYNTAX	INTEGER
			MAX-ACCESS	read-only
			STATUS	current
			::= { hmWanMbus41 26 }

hmWanMbus41Value0A		OBJECT-TYPE
			SYNTAX	INTEGER
			MAX-ACCESS	read-only
			STATUS	current
			::= { hmWanMbus41 27 }

hmWanMbus41VIF0B		OBJECT-TYPE
			SYNTAX	INTEGER
			MAX-ACCESS	read-only
			STATUS	current
			::= { hmWanMbus41 28 }

hmWanMbus41Value0B		OBJECT-TYPE
			SYNTAX	INTEGER
			MAX-ACCESS	read-only
			STATUS	current
			::= { hmWanMbus41 29 }

hmWanMbus41VIF0C		OBJECT-TYPE
			SYNTAX	INTEGER
			MAX-ACCESS	read-only
			STATUS	current
			::= { hmWanMbus41 30 }

hmWanMbus41Value0C		OBJECT-TYPE
			SYNTAX	INTEGER
			MAX-ACCESS	read-only
			STATUS	current
			::= { hmWanMbus41 31 }

hmWanMbus41VIF0D		OBJECT-TYPE
			SYNTAX	INTEGER
			MAX-ACCESS	read-only
			STATUS	current
			::= { hmWanMbus41 32 }

hmWanMbus41Value0D		OBJECT-TYPE
			SYNTAX	INTEGER
			MAX-ACCESS	read-only
			STATUS	current
			::= { hmWanMbus41 33 }

hmWanMbus41VIF0E		OBJECT-TYPE
			SYNTAX	INTEGER
			MAX-ACCESS	read-only
			STATUS	current
			::= { hmWanMbus41 34 }

hmWanMbus41Value0E		OBJECT-TYPE
			SYNTAX	INTEGER
			MAX-ACCESS	read-only
			STATUS	current
			::= { hmWanMbus41 35 }

hmWanMbus41VIF0F		OBJECT-TYPE
			SYNTAX	INTEGER
			MAX-ACCESS	read-only
			STATUS	current
			::= { hmWanMbus41 36 }

hmWanMbus41Value0F		OBJECT-TYPE
			SYNTAX	INTEGER
			MAX-ACCESS	read-only
			STATUS	current
			::= { hmWanMbus41 37 }

hmWanMbus41VIF10		OBJECT-TYPE
			SYNTAX	INTEGER
			MAX-ACCESS	read-only
			STATUS	current
			::= { hmWanMbus41 38 }

hmWanMbus41Value10		OBJECT-TYPE
			SYNTAX	INTEGER
			MAX-ACCESS	read-only
			STATUS	current
			::= { hmWanMbus41 39 }

hmWanMbus41VIF11		OBJECT-TYPE
			SYNTAX	INTEGER
			MAX-ACCESS	read-only
			STATUS	current
			::= { hmWanMbus41 40 }

hmWanMbus41Value11		OBJECT-TYPE
			SYNTAX	INTEGER
			MAX-ACCESS	read-only
			STATUS	current
			::= { hmWanMbus41 41 }

hmWanMbus41VIF12		OBJECT-TYPE
			SYNTAX	INTEGER
			MAX-ACCESS	read-only
			STATUS	current
			::= { hmWanMbus41 42 }

hmWanMbus41Value12		OBJECT-TYPE
			SYNTAX	INTEGER
			MAX-ACCESS	read-only
			STATUS	current
			::= { hmWanMbus41 43 }

hmWanMbus41VIF13		OBJECT-TYPE
			SYNTAX	INTEGER
			MAX-ACCESS	read-only
			STATUS	current
			::= { hmWanMbus41 44 }

hmWanMbus41Value13		OBJECT-TYPE
			SYNTAX	INTEGER
			MAX-ACCESS	read-only
			STATUS	current
			::= { hmWanMbus41 45 }

hmWanMbus41VIF14		OBJECT-TYPE
			SYNTAX	INTEGER
			MAX-ACCESS	read-only
			STATUS	current
			::= { hmWanMbus41 46 }

hmWanMbus41Value14		OBJECT-TYPE
			SYNTAX	INTEGER
			MAX-ACCESS	read-only
			STATUS	current
			::= { hmWanMbus41 47 }

hmWanMbus41VIF15		OBJECT-TYPE
			SYNTAX	INTEGER
			MAX-ACCESS	read-only
			STATUS	current
			::= { hmWanMbus41 48 }

hmWanMbus41Value15		OBJECT-TYPE
			SYNTAX	INTEGER
			MAX-ACCESS	read-only
			STATUS	current
			::= { hmWanMbus41 49 }

hmWanMbus41VIF16		OBJECT-TYPE
			SYNTAX	INTEGER
			MAX-ACCESS	read-only
			STATUS	current
			::= { hmWanMbus41 50 }

hmWanMbus41Value16		OBJECT-TYPE
			SYNTAX	INTEGER
			MAX-ACCESS	read-only
			STATUS	current
			::= { hmWanMbus41 51 }

hmWanMbus41VIF17		OBJECT-TYPE
			SYNTAX	INTEGER
			MAX-ACCESS	read-only
			STATUS	current
			::= { hmWanMbus41 52 }

hmWanMbus41Value17		OBJECT-TYPE
			SYNTAX	INTEGER
			MAX-ACCESS	read-only
			STATUS	current
			::= { hmWanMbus41 53 }

hmWanMbus41VIF18		OBJECT-TYPE
			SYNTAX	INTEGER
			MAX-ACCESS	read-only
			STATUS	current
			::= { hmWanMbus41 54 }

hmWanMbus41Value18		OBJECT-TYPE
			SYNTAX	INTEGER
			MAX-ACCESS	read-only
			STATUS	current
			::= { hmWanMbus41 55 }

hmWanMbus41VIF19		OBJECT-TYPE
			SYNTAX	INTEGER
			MAX-ACCESS	read-only
			STATUS	current
			::= { hmWanMbus41 56 }

hmWanMbus41Value19		OBJECT-TYPE
			SYNTAX	INTEGER
			MAX-ACCESS	read-only
			STATUS	current
			::= { hmWanMbus41 57 }

hmWanMbus41VIF1A		OBJECT-TYPE
			SYNTAX	INTEGER
			MAX-ACCESS	read-only
			STATUS	current
			::= { hmWanMbus41 58 }

hmWanMbus41Value1A		OBJECT-TYPE
			SYNTAX	INTEGER
			MAX-ACCESS	read-only
			STATUS	current
			::= { hmWanMbus41 59 }

hmWanMbus41VIF1B		OBJECT-TYPE
			SYNTAX	INTEGER
			MAX-ACCESS	read-only
			STATUS	current
			::= { hmWanMbus41 60 }

hmWanMbus41Value1B		OBJECT-TYPE
			SYNTAX	INTEGER
			MAX-ACCESS	read-only
			STATUS	current
			::= { hmWanMbus41 61 }

hmWanMbus41VIF1C		OBJECT-TYPE
			SYNTAX	INTEGER
			MAX-ACCESS	read-only
			STATUS	current
			::= { hmWanMbus41 62 }

hmWanMbus41Value1C		OBJECT-TYPE
			SYNTAX	INTEGER
			MAX-ACCESS	read-only
			STATUS	current
			::= { hmWanMbus41 63 }

hmWanMbus41VIF1D		OBJECT-TYPE
			SYNTAX	INTEGER
			MAX-ACCESS	read-only
			STATUS	current
			::= { hmWanMbus41 64 }

hmWanMbus41Value1D		OBJECT-TYPE
			SYNTAX	INTEGER
			MAX-ACCESS	read-only
			STATUS	current
			::= { hmWanMbus41 65 }

hmWanMbus41VIF1E		OBJECT-TYPE
			SYNTAX	INTEGER
			MAX-ACCESS	read-only
			STATUS	current
			::= { hmWanMbus41 66 }

hmWanMbus41Value1E		OBJECT-TYPE
			SYNTAX	INTEGER
			MAX-ACCESS	read-only
			STATUS	current
			::= { hmWanMbus41 67 }

hmWanMbus41VIF1F		OBJECT-TYPE
			SYNTAX	INTEGER
			MAX-ACCESS	read-only
			STATUS	current
			::= { hmWanMbus41 68 }

hmWanMbus41Value1F		OBJECT-TYPE
			SYNTAX	INTEGER
			MAX-ACCESS	read-only
			STATUS	current
			::= { hmWanMbus41 69 }

hmWanMbus41VIF20		OBJECT-TYPE
			SYNTAX	INTEGER
			MAX-ACCESS	read-only
			STATUS	current
			::= { hmWanMbus41 70 }

hmWanMbus41Value20		OBJECT-TYPE
			SYNTAX	INTEGER
			MAX-ACCESS	read-only
			STATUS	current
			::= { hmWanMbus41 71 }

hmWanMbus41VIF21		OBJECT-TYPE
			SYNTAX	INTEGER
			MAX-ACCESS	read-only
			STATUS	current
			::= { hmWanMbus41 72 }

hmWanMbus41Value21		OBJECT-TYPE
			SYNTAX	INTEGER
			MAX-ACCESS	read-only
			STATUS	current
			::= { hmWanMbus41 73 }

hmWanMbus41VIF22		OBJECT-TYPE
			SYNTAX	INTEGER
			MAX-ACCESS	read-only
			STATUS	current
			::= { hmWanMbus41 74 }

hmWanMbus41Value22		OBJECT-TYPE
			SYNTAX	INTEGER
			MAX-ACCESS	read-only
			STATUS	current
			::= { hmWanMbus41 75 }

hmWanMbus41VIF23		OBJECT-TYPE
			SYNTAX	INTEGER
			MAX-ACCESS	read-only
			STATUS	current
			::= { hmWanMbus41 76 }

hmWanMbus41Value23		OBJECT-TYPE
			SYNTAX	INTEGER
			MAX-ACCESS	read-only
			STATUS	current
			::= { hmWanMbus41 77 }

hmWanMbus41VIF24		OBJECT-TYPE
			SYNTAX	INTEGER
			MAX-ACCESS	read-only
			STATUS	current
			::= { hmWanMbus41 78 }

hmWanMbus41Value24		OBJECT-TYPE
			SYNTAX	INTEGER
			MAX-ACCESS	read-only
			STATUS	current
			::= { hmWanMbus41 79 }

hmWanMbus41VIF25		OBJECT-TYPE
			SYNTAX	INTEGER
			MAX-ACCESS	read-only
			STATUS	current
			::= { hmWanMbus41 80 }

hmWanMbus41Value25		OBJECT-TYPE
			SYNTAX	INTEGER
			MAX-ACCESS	read-only
			STATUS	current
			::= { hmWanMbus41 81 }

hmWanMbus41VIF26		OBJECT-TYPE
			SYNTAX	INTEGER
			MAX-ACCESS	read-only
			STATUS	current
			::= { hmWanMbus41 82 }

hmWanMbus41Value26		OBJECT-TYPE
			SYNTAX	INTEGER
			MAX-ACCESS	read-only
			STATUS	current
			::= { hmWanMbus41 83 }

hmWanMbus41VIF27		OBJECT-TYPE
			SYNTAX	INTEGER
			MAX-ACCESS	read-only
			STATUS	current
			::= { hmWanMbus41 84 }

hmWanMbus41Value27		OBJECT-TYPE
			SYNTAX	INTEGER
			MAX-ACCESS	read-only
			STATUS	current
			::= { hmWanMbus41 85 }

hmWanMbus41VIF28		OBJECT-TYPE
			SYNTAX	INTEGER
			MAX-ACCESS	read-only
			STATUS	current
			::= { hmWanMbus41 86 }

hmWanMbus41Value28		OBJECT-TYPE
			SYNTAX	INTEGER
			MAX-ACCESS	read-only
			STATUS	current
			::= { hmWanMbus41 87 }

hmWanMbus41VIF29		OBJECT-TYPE
			SYNTAX	INTEGER
			MAX-ACCESS	read-only
			STATUS	current
			::= { hmWanMbus41 88 }

hmWanMbus41Value29		OBJECT-TYPE
			SYNTAX	INTEGER
			MAX-ACCESS	read-only
			STATUS	current
			::= { hmWanMbus41 89 }

hmWanMbus41VIF2A		OBJECT-TYPE
			SYNTAX	INTEGER
			MAX-ACCESS	read-only
			STATUS	current
			::= { hmWanMbus41 90 }

hmWanMbus41Value2A		OBJECT-TYPE
			SYNTAX	INTEGER
			MAX-ACCESS	read-only
			STATUS	current
			::= { hmWanMbus41 91 }

hmWanMbus41VIF2B		OBJECT-TYPE
			SYNTAX	INTEGER
			MAX-ACCESS	read-only
			STATUS	current
			::= { hmWanMbus41 92 }

hmWanMbus41Value2B		OBJECT-TYPE
			SYNTAX	INTEGER
			MAX-ACCESS	read-only
			STATUS	current
			::= { hmWanMbus41 93 }

hmWanMbus41VIF2C		OBJECT-TYPE
			SYNTAX	INTEGER
			MAX-ACCESS	read-only
			STATUS	current
			::= { hmWanMbus41 94 }

hmWanMbus41Value2C		OBJECT-TYPE
			SYNTAX	INTEGER
			MAX-ACCESS	read-only
			STATUS	current
			::= { hmWanMbus41 95 }

hmWanMbus41VIF2D		OBJECT-TYPE
			SYNTAX	INTEGER
			MAX-ACCESS	read-only
			STATUS	current
			::= { hmWanMbus41 96 }

hmWanMbus41Value2D		OBJECT-TYPE
			SYNTAX	INTEGER
			MAX-ACCESS	read-only
			STATUS	current
			::= { hmWanMbus41 97 }

hmWanMbus41VIF2E		OBJECT-TYPE
			SYNTAX	INTEGER
			MAX-ACCESS	read-only
			STATUS	current
			::= { hmWanMbus41 98 }

hmWanMbus41Value2E		OBJECT-TYPE
			SYNTAX	INTEGER
			MAX-ACCESS	read-only
			STATUS	current
			::= { hmWanMbus41 99 }

hmWanMbus41VIF2F		OBJECT-TYPE
			SYNTAX	INTEGER
			MAX-ACCESS	read-only
			STATUS	current
			::= { hmWanMbus41 100 }

hmWanMbus41Value2F		OBJECT-TYPE
			SYNTAX	INTEGER
			MAX-ACCESS	read-only
			STATUS	current
			::= { hmWanMbus41 101 }

hmWanMbus42			OBJECT IDENTIFIER ::= { hmWanMbus 66 }

hmWanMbus42IdNumber		OBJECT-TYPE
			SYNTAX	Gauge32
			MAX-ACCESS	read-only
			STATUS	current
			::= { hmWanMbus42 1 }

hmWanMbus42Manufacturer	OBJECT-TYPE
			SYNTAX	Gauge32
			MAX-ACCESS	read-only
			STATUS	current
			::= { hmWanMbus42 2 }

hmWanMbus42Version		OBJECT-TYPE
			SYNTAX	Gauge32
			MAX-ACCESS	read-only
			STATUS	current
			::= { hmWanMbus42 3 }

hmWanMbus42Medium		OBJECT-TYPE
			SYNTAX	Gauge32
			MAX-ACCESS	read-only
			STATUS	current
			::= { hmWanMbus42 4 }

hmWanMbus42Status		OBJECT-TYPE
			SYNTAX	Gauge32
			MAX-ACCESS	read-only
			STATUS	current
			::= { hmWanMbus42 5 }

hmWanMbus42VIF00		OBJECT-TYPE
			SYNTAX	INTEGER
			MAX-ACCESS	read-only
			STATUS	current
			::= { hmWanMbus42 6 }

hmWanMbus42Value00		OBJECT-TYPE
			SYNTAX	INTEGER
			MAX-ACCESS	read-only
			STATUS	current
			::= { hmWanMbus42 7 }

hmWanMbus42VIF01		OBJECT-TYPE
			SYNTAX	INTEGER
			MAX-ACCESS	read-only
			STATUS	current
			::= { hmWanMbus42 8 }

hmWanMbus42Value01		OBJECT-TYPE
			SYNTAX	INTEGER
			MAX-ACCESS	read-only
			STATUS	current
			::= { hmWanMbus42 9 }

hmWanMbus42VIF02		OBJECT-TYPE
			SYNTAX	INTEGER
			MAX-ACCESS	read-only
			STATUS	current
			::= { hmWanMbus42 10 }

hmWanMbus42Value02		OBJECT-TYPE
			SYNTAX	INTEGER
			MAX-ACCESS	read-only
			STATUS	current
			::= { hmWanMbus42 11 }

hmWanMbus42VIF03		OBJECT-TYPE
			SYNTAX	INTEGER
			MAX-ACCESS	read-only
			STATUS	current
			::= { hmWanMbus42 12 }

hmWanMbus42Value03		OBJECT-TYPE
			SYNTAX	INTEGER
			MAX-ACCESS	read-only
			STATUS	current
			::= { hmWanMbus42 13 }

hmWanMbus42VIF04		OBJECT-TYPE
			SYNTAX	INTEGER
			MAX-ACCESS	read-only
			STATUS	current
			::= { hmWanMbus42 14 }

hmWanMbus42Value04		OBJECT-TYPE
			SYNTAX	INTEGER
			MAX-ACCESS	read-only
			STATUS	current
			::= { hmWanMbus42 15 }

hmWanMbus42VIF05		OBJECT-TYPE
			SYNTAX	INTEGER
			MAX-ACCESS	read-only
			STATUS	current
			::= { hmWanMbus42 16 }

hmWanMbus42Value05		OBJECT-TYPE
			SYNTAX	INTEGER
			MAX-ACCESS	read-only
			STATUS	current
			::= { hmWanMbus42 17 }

hmWanMbus42VIF06		OBJECT-TYPE
			SYNTAX	INTEGER
			MAX-ACCESS	read-only
			STATUS	current
			::= { hmWanMbus42 18 }

hmWanMbus42Value06		OBJECT-TYPE
			SYNTAX	INTEGER
			MAX-ACCESS	read-only
			STATUS	current
			::= { hmWanMbus42 19 }

hmWanMbus42VIF07		OBJECT-TYPE
			SYNTAX	INTEGER
			MAX-ACCESS	read-only
			STATUS	current
			::= { hmWanMbus42 20 }

hmWanMbus42Value07		OBJECT-TYPE
			SYNTAX	INTEGER
			MAX-ACCESS	read-only
			STATUS	current
			::= { hmWanMbus42 21 }

hmWanMbus42VIF08		OBJECT-TYPE
			SYNTAX	INTEGER
			MAX-ACCESS	read-only
			STATUS	current
			::= { hmWanMbus42 22 }

hmWanMbus42Value08		OBJECT-TYPE
			SYNTAX	INTEGER
			MAX-ACCESS	read-only
			STATUS	current
			::= { hmWanMbus42 23 }

hmWanMbus42VIF09		OBJECT-TYPE
			SYNTAX	INTEGER
			MAX-ACCESS	read-only
			STATUS	current
			::= { hmWanMbus42 24 }

hmWanMbus42Value09		OBJECT-TYPE
			SYNTAX	INTEGER
			MAX-ACCESS	read-only
			STATUS	current
			::= { hmWanMbus42 25 }

hmWanMbus42VIF0A		OBJECT-TYPE
			SYNTAX	INTEGER
			MAX-ACCESS	read-only
			STATUS	current
			::= { hmWanMbus42 26 }

hmWanMbus42Value0A		OBJECT-TYPE
			SYNTAX	INTEGER
			MAX-ACCESS	read-only
			STATUS	current
			::= { hmWanMbus42 27 }

hmWanMbus42VIF0B		OBJECT-TYPE
			SYNTAX	INTEGER
			MAX-ACCESS	read-only
			STATUS	current
			::= { hmWanMbus42 28 }

hmWanMbus42Value0B		OBJECT-TYPE
			SYNTAX	INTEGER
			MAX-ACCESS	read-only
			STATUS	current
			::= { hmWanMbus42 29 }

hmWanMbus42VIF0C		OBJECT-TYPE
			SYNTAX	INTEGER
			MAX-ACCESS	read-only
			STATUS	current
			::= { hmWanMbus42 30 }

hmWanMbus42Value0C		OBJECT-TYPE
			SYNTAX	INTEGER
			MAX-ACCESS	read-only
			STATUS	current
			::= { hmWanMbus42 31 }

hmWanMbus42VIF0D		OBJECT-TYPE
			SYNTAX	INTEGER
			MAX-ACCESS	read-only
			STATUS	current
			::= { hmWanMbus42 32 }

hmWanMbus42Value0D		OBJECT-TYPE
			SYNTAX	INTEGER
			MAX-ACCESS	read-only
			STATUS	current
			::= { hmWanMbus42 33 }

hmWanMbus42VIF0E		OBJECT-TYPE
			SYNTAX	INTEGER
			MAX-ACCESS	read-only
			STATUS	current
			::= { hmWanMbus42 34 }

hmWanMbus42Value0E		OBJECT-TYPE
			SYNTAX	INTEGER
			MAX-ACCESS	read-only
			STATUS	current
			::= { hmWanMbus42 35 }

hmWanMbus42VIF0F		OBJECT-TYPE
			SYNTAX	INTEGER
			MAX-ACCESS	read-only
			STATUS	current
			::= { hmWanMbus42 36 }

hmWanMbus42Value0F		OBJECT-TYPE
			SYNTAX	INTEGER
			MAX-ACCESS	read-only
			STATUS	current
			::= { hmWanMbus42 37 }

hmWanMbus42VIF10		OBJECT-TYPE
			SYNTAX	INTEGER
			MAX-ACCESS	read-only
			STATUS	current
			::= { hmWanMbus42 38 }

hmWanMbus42Value10		OBJECT-TYPE
			SYNTAX	INTEGER
			MAX-ACCESS	read-only
			STATUS	current
			::= { hmWanMbus42 39 }

hmWanMbus42VIF11		OBJECT-TYPE
			SYNTAX	INTEGER
			MAX-ACCESS	read-only
			STATUS	current
			::= { hmWanMbus42 40 }

hmWanMbus42Value11		OBJECT-TYPE
			SYNTAX	INTEGER
			MAX-ACCESS	read-only
			STATUS	current
			::= { hmWanMbus42 41 }

hmWanMbus42VIF12		OBJECT-TYPE
			SYNTAX	INTEGER
			MAX-ACCESS	read-only
			STATUS	current
			::= { hmWanMbus42 42 }

hmWanMbus42Value12		OBJECT-TYPE
			SYNTAX	INTEGER
			MAX-ACCESS	read-only
			STATUS	current
			::= { hmWanMbus42 43 }

hmWanMbus42VIF13		OBJECT-TYPE
			SYNTAX	INTEGER
			MAX-ACCESS	read-only
			STATUS	current
			::= { hmWanMbus42 44 }

hmWanMbus42Value13		OBJECT-TYPE
			SYNTAX	INTEGER
			MAX-ACCESS	read-only
			STATUS	current
			::= { hmWanMbus42 45 }

hmWanMbus42VIF14		OBJECT-TYPE
			SYNTAX	INTEGER
			MAX-ACCESS	read-only
			STATUS	current
			::= { hmWanMbus42 46 }

hmWanMbus42Value14		OBJECT-TYPE
			SYNTAX	INTEGER
			MAX-ACCESS	read-only
			STATUS	current
			::= { hmWanMbus42 47 }

hmWanMbus42VIF15		OBJECT-TYPE
			SYNTAX	INTEGER
			MAX-ACCESS	read-only
			STATUS	current
			::= { hmWanMbus42 48 }

hmWanMbus42Value15		OBJECT-TYPE
			SYNTAX	INTEGER
			MAX-ACCESS	read-only
			STATUS	current
			::= { hmWanMbus42 49 }

hmWanMbus42VIF16		OBJECT-TYPE
			SYNTAX	INTEGER
			MAX-ACCESS	read-only
			STATUS	current
			::= { hmWanMbus42 50 }

hmWanMbus42Value16		OBJECT-TYPE
			SYNTAX	INTEGER
			MAX-ACCESS	read-only
			STATUS	current
			::= { hmWanMbus42 51 }

hmWanMbus42VIF17		OBJECT-TYPE
			SYNTAX	INTEGER
			MAX-ACCESS	read-only
			STATUS	current
			::= { hmWanMbus42 52 }

hmWanMbus42Value17		OBJECT-TYPE
			SYNTAX	INTEGER
			MAX-ACCESS	read-only
			STATUS	current
			::= { hmWanMbus42 53 }

hmWanMbus42VIF18		OBJECT-TYPE
			SYNTAX	INTEGER
			MAX-ACCESS	read-only
			STATUS	current
			::= { hmWanMbus42 54 }

hmWanMbus42Value18		OBJECT-TYPE
			SYNTAX	INTEGER
			MAX-ACCESS	read-only
			STATUS	current
			::= { hmWanMbus42 55 }

hmWanMbus42VIF19		OBJECT-TYPE
			SYNTAX	INTEGER
			MAX-ACCESS	read-only
			STATUS	current
			::= { hmWanMbus42 56 }

hmWanMbus42Value19		OBJECT-TYPE
			SYNTAX	INTEGER
			MAX-ACCESS	read-only
			STATUS	current
			::= { hmWanMbus42 57 }

hmWanMbus42VIF1A		OBJECT-TYPE
			SYNTAX	INTEGER
			MAX-ACCESS	read-only
			STATUS	current
			::= { hmWanMbus42 58 }

hmWanMbus42Value1A		OBJECT-TYPE
			SYNTAX	INTEGER
			MAX-ACCESS	read-only
			STATUS	current
			::= { hmWanMbus42 59 }

hmWanMbus42VIF1B		OBJECT-TYPE
			SYNTAX	INTEGER
			MAX-ACCESS	read-only
			STATUS	current
			::= { hmWanMbus42 60 }

hmWanMbus42Value1B		OBJECT-TYPE
			SYNTAX	INTEGER
			MAX-ACCESS	read-only
			STATUS	current
			::= { hmWanMbus42 61 }

hmWanMbus42VIF1C		OBJECT-TYPE
			SYNTAX	INTEGER
			MAX-ACCESS	read-only
			STATUS	current
			::= { hmWanMbus42 62 }

hmWanMbus42Value1C		OBJECT-TYPE
			SYNTAX	INTEGER
			MAX-ACCESS	read-only
			STATUS	current
			::= { hmWanMbus42 63 }

hmWanMbus42VIF1D		OBJECT-TYPE
			SYNTAX	INTEGER
			MAX-ACCESS	read-only
			STATUS	current
			::= { hmWanMbus42 64 }

hmWanMbus42Value1D		OBJECT-TYPE
			SYNTAX	INTEGER
			MAX-ACCESS	read-only
			STATUS	current
			::= { hmWanMbus42 65 }

hmWanMbus42VIF1E		OBJECT-TYPE
			SYNTAX	INTEGER
			MAX-ACCESS	read-only
			STATUS	current
			::= { hmWanMbus42 66 }

hmWanMbus42Value1E		OBJECT-TYPE
			SYNTAX	INTEGER
			MAX-ACCESS	read-only
			STATUS	current
			::= { hmWanMbus42 67 }

hmWanMbus42VIF1F		OBJECT-TYPE
			SYNTAX	INTEGER
			MAX-ACCESS	read-only
			STATUS	current
			::= { hmWanMbus42 68 }

hmWanMbus42Value1F		OBJECT-TYPE
			SYNTAX	INTEGER
			MAX-ACCESS	read-only
			STATUS	current
			::= { hmWanMbus42 69 }

hmWanMbus42VIF20		OBJECT-TYPE
			SYNTAX	INTEGER
			MAX-ACCESS	read-only
			STATUS	current
			::= { hmWanMbus42 70 }

hmWanMbus42Value20		OBJECT-TYPE
			SYNTAX	INTEGER
			MAX-ACCESS	read-only
			STATUS	current
			::= { hmWanMbus42 71 }

hmWanMbus42VIF21		OBJECT-TYPE
			SYNTAX	INTEGER
			MAX-ACCESS	read-only
			STATUS	current
			::= { hmWanMbus42 72 }

hmWanMbus42Value21		OBJECT-TYPE
			SYNTAX	INTEGER
			MAX-ACCESS	read-only
			STATUS	current
			::= { hmWanMbus42 73 }

hmWanMbus42VIF22		OBJECT-TYPE
			SYNTAX	INTEGER
			MAX-ACCESS	read-only
			STATUS	current
			::= { hmWanMbus42 74 }

hmWanMbus42Value22		OBJECT-TYPE
			SYNTAX	INTEGER
			MAX-ACCESS	read-only
			STATUS	current
			::= { hmWanMbus42 75 }

hmWanMbus42VIF23		OBJECT-TYPE
			SYNTAX	INTEGER
			MAX-ACCESS	read-only
			STATUS	current
			::= { hmWanMbus42 76 }

hmWanMbus42Value23		OBJECT-TYPE
			SYNTAX	INTEGER
			MAX-ACCESS	read-only
			STATUS	current
			::= { hmWanMbus42 77 }

hmWanMbus42VIF24		OBJECT-TYPE
			SYNTAX	INTEGER
			MAX-ACCESS	read-only
			STATUS	current
			::= { hmWanMbus42 78 }

hmWanMbus42Value24		OBJECT-TYPE
			SYNTAX	INTEGER
			MAX-ACCESS	read-only
			STATUS	current
			::= { hmWanMbus42 79 }

hmWanMbus42VIF25		OBJECT-TYPE
			SYNTAX	INTEGER
			MAX-ACCESS	read-only
			STATUS	current
			::= { hmWanMbus42 80 }

hmWanMbus42Value25		OBJECT-TYPE
			SYNTAX	INTEGER
			MAX-ACCESS	read-only
			STATUS	current
			::= { hmWanMbus42 81 }

hmWanMbus42VIF26		OBJECT-TYPE
			SYNTAX	INTEGER
			MAX-ACCESS	read-only
			STATUS	current
			::= { hmWanMbus42 82 }

hmWanMbus42Value26		OBJECT-TYPE
			SYNTAX	INTEGER
			MAX-ACCESS	read-only
			STATUS	current
			::= { hmWanMbus42 83 }

hmWanMbus42VIF27		OBJECT-TYPE
			SYNTAX	INTEGER
			MAX-ACCESS	read-only
			STATUS	current
			::= { hmWanMbus42 84 }

hmWanMbus42Value27		OBJECT-TYPE
			SYNTAX	INTEGER
			MAX-ACCESS	read-only
			STATUS	current
			::= { hmWanMbus42 85 }

hmWanMbus42VIF28		OBJECT-TYPE
			SYNTAX	INTEGER
			MAX-ACCESS	read-only
			STATUS	current
			::= { hmWanMbus42 86 }

hmWanMbus42Value28		OBJECT-TYPE
			SYNTAX	INTEGER
			MAX-ACCESS	read-only
			STATUS	current
			::= { hmWanMbus42 87 }

hmWanMbus42VIF29		OBJECT-TYPE
			SYNTAX	INTEGER
			MAX-ACCESS	read-only
			STATUS	current
			::= { hmWanMbus42 88 }

hmWanMbus42Value29		OBJECT-TYPE
			SYNTAX	INTEGER
			MAX-ACCESS	read-only
			STATUS	current
			::= { hmWanMbus42 89 }

hmWanMbus42VIF2A		OBJECT-TYPE
			SYNTAX	INTEGER
			MAX-ACCESS	read-only
			STATUS	current
			::= { hmWanMbus42 90 }

hmWanMbus42Value2A		OBJECT-TYPE
			SYNTAX	INTEGER
			MAX-ACCESS	read-only
			STATUS	current
			::= { hmWanMbus42 91 }

hmWanMbus42VIF2B		OBJECT-TYPE
			SYNTAX	INTEGER
			MAX-ACCESS	read-only
			STATUS	current
			::= { hmWanMbus42 92 }

hmWanMbus42Value2B		OBJECT-TYPE
			SYNTAX	INTEGER
			MAX-ACCESS	read-only
			STATUS	current
			::= { hmWanMbus42 93 }

hmWanMbus42VIF2C		OBJECT-TYPE
			SYNTAX	INTEGER
			MAX-ACCESS	read-only
			STATUS	current
			::= { hmWanMbus42 94 }

hmWanMbus42Value2C		OBJECT-TYPE
			SYNTAX	INTEGER
			MAX-ACCESS	read-only
			STATUS	current
			::= { hmWanMbus42 95 }

hmWanMbus42VIF2D		OBJECT-TYPE
			SYNTAX	INTEGER
			MAX-ACCESS	read-only
			STATUS	current
			::= { hmWanMbus42 96 }

hmWanMbus42Value2D		OBJECT-TYPE
			SYNTAX	INTEGER
			MAX-ACCESS	read-only
			STATUS	current
			::= { hmWanMbus42 97 }

hmWanMbus42VIF2E		OBJECT-TYPE
			SYNTAX	INTEGER
			MAX-ACCESS	read-only
			STATUS	current
			::= { hmWanMbus42 98 }

hmWanMbus42Value2E		OBJECT-TYPE
			SYNTAX	INTEGER
			MAX-ACCESS	read-only
			STATUS	current
			::= { hmWanMbus42 99 }

hmWanMbus42VIF2F		OBJECT-TYPE
			SYNTAX	INTEGER
			MAX-ACCESS	read-only
			STATUS	current
			::= { hmWanMbus42 100 }

hmWanMbus42Value2F		OBJECT-TYPE
			SYNTAX	INTEGER
			MAX-ACCESS	read-only
			STATUS	current
			::= { hmWanMbus42 101 }

hmWanMbus43			OBJECT IDENTIFIER ::= { hmWanMbus 67 }

hmWanMbus43IdNumber		OBJECT-TYPE
			SYNTAX	Gauge32
			MAX-ACCESS	read-only
			STATUS	current
			::= { hmWanMbus43 1 }

hmWanMbus43Manufacturer	OBJECT-TYPE
			SYNTAX	Gauge32
			MAX-ACCESS	read-only
			STATUS	current
			::= { hmWanMbus43 2 }

hmWanMbus43Version		OBJECT-TYPE
			SYNTAX	Gauge32
			MAX-ACCESS	read-only
			STATUS	current
			::= { hmWanMbus43 3 }

hmWanMbus43Medium		OBJECT-TYPE
			SYNTAX	Gauge32
			MAX-ACCESS	read-only
			STATUS	current
			::= { hmWanMbus43 4 }

hmWanMbus43Status		OBJECT-TYPE
			SYNTAX	Gauge32
			MAX-ACCESS	read-only
			STATUS	current
			::= { hmWanMbus43 5 }

hmWanMbus43VIF00		OBJECT-TYPE
			SYNTAX	INTEGER
			MAX-ACCESS	read-only
			STATUS	current
			::= { hmWanMbus43 6 }

hmWanMbus43Value00		OBJECT-TYPE
			SYNTAX	INTEGER
			MAX-ACCESS	read-only
			STATUS	current
			::= { hmWanMbus43 7 }

hmWanMbus43VIF01		OBJECT-TYPE
			SYNTAX	INTEGER
			MAX-ACCESS	read-only
			STATUS	current
			::= { hmWanMbus43 8 }

hmWanMbus43Value01		OBJECT-TYPE
			SYNTAX	INTEGER
			MAX-ACCESS	read-only
			STATUS	current
			::= { hmWanMbus43 9 }

hmWanMbus43VIF02		OBJECT-TYPE
			SYNTAX	INTEGER
			MAX-ACCESS	read-only
			STATUS	current
			::= { hmWanMbus43 10 }

hmWanMbus43Value02		OBJECT-TYPE
			SYNTAX	INTEGER
			MAX-ACCESS	read-only
			STATUS	current
			::= { hmWanMbus43 11 }

hmWanMbus43VIF03		OBJECT-TYPE
			SYNTAX	INTEGER
			MAX-ACCESS	read-only
			STATUS	current
			::= { hmWanMbus43 12 }

hmWanMbus43Value03		OBJECT-TYPE
			SYNTAX	INTEGER
			MAX-ACCESS	read-only
			STATUS	current
			::= { hmWanMbus43 13 }

hmWanMbus43VIF04		OBJECT-TYPE
			SYNTAX	INTEGER
			MAX-ACCESS	read-only
			STATUS	current
			::= { hmWanMbus43 14 }

hmWanMbus43Value04		OBJECT-TYPE
			SYNTAX	INTEGER
			MAX-ACCESS	read-only
			STATUS	current
			::= { hmWanMbus43 15 }

hmWanMbus43VIF05		OBJECT-TYPE
			SYNTAX	INTEGER
			MAX-ACCESS	read-only
			STATUS	current
			::= { hmWanMbus43 16 }

hmWanMbus43Value05		OBJECT-TYPE
			SYNTAX	INTEGER
			MAX-ACCESS	read-only
			STATUS	current
			::= { hmWanMbus43 17 }

hmWanMbus43VIF06		OBJECT-TYPE
			SYNTAX	INTEGER
			MAX-ACCESS	read-only
			STATUS	current
			::= { hmWanMbus43 18 }

hmWanMbus43Value06		OBJECT-TYPE
			SYNTAX	INTEGER
			MAX-ACCESS	read-only
			STATUS	current
			::= { hmWanMbus43 19 }

hmWanMbus43VIF07		OBJECT-TYPE
			SYNTAX	INTEGER
			MAX-ACCESS	read-only
			STATUS	current
			::= { hmWanMbus43 20 }

hmWanMbus43Value07		OBJECT-TYPE
			SYNTAX	INTEGER
			MAX-ACCESS	read-only
			STATUS	current
			::= { hmWanMbus43 21 }

hmWanMbus43VIF08		OBJECT-TYPE
			SYNTAX	INTEGER
			MAX-ACCESS	read-only
			STATUS	current
			::= { hmWanMbus43 22 }

hmWanMbus43Value08		OBJECT-TYPE
			SYNTAX	INTEGER
			MAX-ACCESS	read-only
			STATUS	current
			::= { hmWanMbus43 23 }

hmWanMbus43VIF09		OBJECT-TYPE
			SYNTAX	INTEGER
			MAX-ACCESS	read-only
			STATUS	current
			::= { hmWanMbus43 24 }

hmWanMbus43Value09		OBJECT-TYPE
			SYNTAX	INTEGER
			MAX-ACCESS	read-only
			STATUS	current
			::= { hmWanMbus43 25 }

hmWanMbus43VIF0A		OBJECT-TYPE
			SYNTAX	INTEGER
			MAX-ACCESS	read-only
			STATUS	current
			::= { hmWanMbus43 26 }

hmWanMbus43Value0A		OBJECT-TYPE
			SYNTAX	INTEGER
			MAX-ACCESS	read-only
			STATUS	current
			::= { hmWanMbus43 27 }

hmWanMbus43VIF0B		OBJECT-TYPE
			SYNTAX	INTEGER
			MAX-ACCESS	read-only
			STATUS	current
			::= { hmWanMbus43 28 }

hmWanMbus43Value0B		OBJECT-TYPE
			SYNTAX	INTEGER
			MAX-ACCESS	read-only
			STATUS	current
			::= { hmWanMbus43 29 }

hmWanMbus43VIF0C		OBJECT-TYPE
			SYNTAX	INTEGER
			MAX-ACCESS	read-only
			STATUS	current
			::= { hmWanMbus43 30 }

hmWanMbus43Value0C		OBJECT-TYPE
			SYNTAX	INTEGER
			MAX-ACCESS	read-only
			STATUS	current
			::= { hmWanMbus43 31 }

hmWanMbus43VIF0D		OBJECT-TYPE
			SYNTAX	INTEGER
			MAX-ACCESS	read-only
			STATUS	current
			::= { hmWanMbus43 32 }

hmWanMbus43Value0D		OBJECT-TYPE
			SYNTAX	INTEGER
			MAX-ACCESS	read-only
			STATUS	current
			::= { hmWanMbus43 33 }

hmWanMbus43VIF0E		OBJECT-TYPE
			SYNTAX	INTEGER
			MAX-ACCESS	read-only
			STATUS	current
			::= { hmWanMbus43 34 }

hmWanMbus43Value0E		OBJECT-TYPE
			SYNTAX	INTEGER
			MAX-ACCESS	read-only
			STATUS	current
			::= { hmWanMbus43 35 }

hmWanMbus43VIF0F		OBJECT-TYPE
			SYNTAX	INTEGER
			MAX-ACCESS	read-only
			STATUS	current
			::= { hmWanMbus43 36 }

hmWanMbus43Value0F		OBJECT-TYPE
			SYNTAX	INTEGER
			MAX-ACCESS	read-only
			STATUS	current
			::= { hmWanMbus43 37 }

hmWanMbus43VIF10		OBJECT-TYPE
			SYNTAX	INTEGER
			MAX-ACCESS	read-only
			STATUS	current
			::= { hmWanMbus43 38 }

hmWanMbus43Value10		OBJECT-TYPE
			SYNTAX	INTEGER
			MAX-ACCESS	read-only
			STATUS	current
			::= { hmWanMbus43 39 }

hmWanMbus43VIF11		OBJECT-TYPE
			SYNTAX	INTEGER
			MAX-ACCESS	read-only
			STATUS	current
			::= { hmWanMbus43 40 }

hmWanMbus43Value11		OBJECT-TYPE
			SYNTAX	INTEGER
			MAX-ACCESS	read-only
			STATUS	current
			::= { hmWanMbus43 41 }

hmWanMbus43VIF12		OBJECT-TYPE
			SYNTAX	INTEGER
			MAX-ACCESS	read-only
			STATUS	current
			::= { hmWanMbus43 42 }

hmWanMbus43Value12		OBJECT-TYPE
			SYNTAX	INTEGER
			MAX-ACCESS	read-only
			STATUS	current
			::= { hmWanMbus43 43 }

hmWanMbus43VIF13		OBJECT-TYPE
			SYNTAX	INTEGER
			MAX-ACCESS	read-only
			STATUS	current
			::= { hmWanMbus43 44 }

hmWanMbus43Value13		OBJECT-TYPE
			SYNTAX	INTEGER
			MAX-ACCESS	read-only
			STATUS	current
			::= { hmWanMbus43 45 }

hmWanMbus43VIF14		OBJECT-TYPE
			SYNTAX	INTEGER
			MAX-ACCESS	read-only
			STATUS	current
			::= { hmWanMbus43 46 }

hmWanMbus43Value14		OBJECT-TYPE
			SYNTAX	INTEGER
			MAX-ACCESS	read-only
			STATUS	current
			::= { hmWanMbus43 47 }

hmWanMbus43VIF15		OBJECT-TYPE
			SYNTAX	INTEGER
			MAX-ACCESS	read-only
			STATUS	current
			::= { hmWanMbus43 48 }

hmWanMbus43Value15		OBJECT-TYPE
			SYNTAX	INTEGER
			MAX-ACCESS	read-only
			STATUS	current
			::= { hmWanMbus43 49 }

hmWanMbus43VIF16		OBJECT-TYPE
			SYNTAX	INTEGER
			MAX-ACCESS	read-only
			STATUS	current
			::= { hmWanMbus43 50 }

hmWanMbus43Value16		OBJECT-TYPE
			SYNTAX	INTEGER
			MAX-ACCESS	read-only
			STATUS	current
			::= { hmWanMbus43 51 }

hmWanMbus43VIF17		OBJECT-TYPE
			SYNTAX	INTEGER
			MAX-ACCESS	read-only
			STATUS	current
			::= { hmWanMbus43 52 }

hmWanMbus43Value17		OBJECT-TYPE
			SYNTAX	INTEGER
			MAX-ACCESS	read-only
			STATUS	current
			::= { hmWanMbus43 53 }

hmWanMbus43VIF18		OBJECT-TYPE
			SYNTAX	INTEGER
			MAX-ACCESS	read-only
			STATUS	current
			::= { hmWanMbus43 54 }

hmWanMbus43Value18		OBJECT-TYPE
			SYNTAX	INTEGER
			MAX-ACCESS	read-only
			STATUS	current
			::= { hmWanMbus43 55 }

hmWanMbus43VIF19		OBJECT-TYPE
			SYNTAX	INTEGER
			MAX-ACCESS	read-only
			STATUS	current
			::= { hmWanMbus43 56 }

hmWanMbus43Value19		OBJECT-TYPE
			SYNTAX	INTEGER
			MAX-ACCESS	read-only
			STATUS	current
			::= { hmWanMbus43 57 }

hmWanMbus43VIF1A		OBJECT-TYPE
			SYNTAX	INTEGER
			MAX-ACCESS	read-only
			STATUS	current
			::= { hmWanMbus43 58 }

hmWanMbus43Value1A		OBJECT-TYPE
			SYNTAX	INTEGER
			MAX-ACCESS	read-only
			STATUS	current
			::= { hmWanMbus43 59 }

hmWanMbus43VIF1B		OBJECT-TYPE
			SYNTAX	INTEGER
			MAX-ACCESS	read-only
			STATUS	current
			::= { hmWanMbus43 60 }

hmWanMbus43Value1B		OBJECT-TYPE
			SYNTAX	INTEGER
			MAX-ACCESS	read-only
			STATUS	current
			::= { hmWanMbus43 61 }

hmWanMbus43VIF1C		OBJECT-TYPE
			SYNTAX	INTEGER
			MAX-ACCESS	read-only
			STATUS	current
			::= { hmWanMbus43 62 }

hmWanMbus43Value1C		OBJECT-TYPE
			SYNTAX	INTEGER
			MAX-ACCESS	read-only
			STATUS	current
			::= { hmWanMbus43 63 }

hmWanMbus43VIF1D		OBJECT-TYPE
			SYNTAX	INTEGER
			MAX-ACCESS	read-only
			STATUS	current
			::= { hmWanMbus43 64 }

hmWanMbus43Value1D		OBJECT-TYPE
			SYNTAX	INTEGER
			MAX-ACCESS	read-only
			STATUS	current
			::= { hmWanMbus43 65 }

hmWanMbus43VIF1E		OBJECT-TYPE
			SYNTAX	INTEGER
			MAX-ACCESS	read-only
			STATUS	current
			::= { hmWanMbus43 66 }

hmWanMbus43Value1E		OBJECT-TYPE
			SYNTAX	INTEGER
			MAX-ACCESS	read-only
			STATUS	current
			::= { hmWanMbus43 67 }

hmWanMbus43VIF1F		OBJECT-TYPE
			SYNTAX	INTEGER
			MAX-ACCESS	read-only
			STATUS	current
			::= { hmWanMbus43 68 }

hmWanMbus43Value1F		OBJECT-TYPE
			SYNTAX	INTEGER
			MAX-ACCESS	read-only
			STATUS	current
			::= { hmWanMbus43 69 }

hmWanMbus43VIF20		OBJECT-TYPE
			SYNTAX	INTEGER
			MAX-ACCESS	read-only
			STATUS	current
			::= { hmWanMbus43 70 }

hmWanMbus43Value20		OBJECT-TYPE
			SYNTAX	INTEGER
			MAX-ACCESS	read-only
			STATUS	current
			::= { hmWanMbus43 71 }

hmWanMbus43VIF21		OBJECT-TYPE
			SYNTAX	INTEGER
			MAX-ACCESS	read-only
			STATUS	current
			::= { hmWanMbus43 72 }

hmWanMbus43Value21		OBJECT-TYPE
			SYNTAX	INTEGER
			MAX-ACCESS	read-only
			STATUS	current
			::= { hmWanMbus43 73 }

hmWanMbus43VIF22		OBJECT-TYPE
			SYNTAX	INTEGER
			MAX-ACCESS	read-only
			STATUS	current
			::= { hmWanMbus43 74 }

hmWanMbus43Value22		OBJECT-TYPE
			SYNTAX	INTEGER
			MAX-ACCESS	read-only
			STATUS	current
			::= { hmWanMbus43 75 }

hmWanMbus43VIF23		OBJECT-TYPE
			SYNTAX	INTEGER
			MAX-ACCESS	read-only
			STATUS	current
			::= { hmWanMbus43 76 }

hmWanMbus43Value23		OBJECT-TYPE
			SYNTAX	INTEGER
			MAX-ACCESS	read-only
			STATUS	current
			::= { hmWanMbus43 77 }

hmWanMbus43VIF24		OBJECT-TYPE
			SYNTAX	INTEGER
			MAX-ACCESS	read-only
			STATUS	current
			::= { hmWanMbus43 78 }

hmWanMbus43Value24		OBJECT-TYPE
			SYNTAX	INTEGER
			MAX-ACCESS	read-only
			STATUS	current
			::= { hmWanMbus43 79 }

hmWanMbus43VIF25		OBJECT-TYPE
			SYNTAX	INTEGER
			MAX-ACCESS	read-only
			STATUS	current
			::= { hmWanMbus43 80 }

hmWanMbus43Value25		OBJECT-TYPE
			SYNTAX	INTEGER
			MAX-ACCESS	read-only
			STATUS	current
			::= { hmWanMbus43 81 }

hmWanMbus43VIF26		OBJECT-TYPE
			SYNTAX	INTEGER
			MAX-ACCESS	read-only
			STATUS	current
			::= { hmWanMbus43 82 }

hmWanMbus43Value26		OBJECT-TYPE
			SYNTAX	INTEGER
			MAX-ACCESS	read-only
			STATUS	current
			::= { hmWanMbus43 83 }

hmWanMbus43VIF27		OBJECT-TYPE
			SYNTAX	INTEGER
			MAX-ACCESS	read-only
			STATUS	current
			::= { hmWanMbus43 84 }

hmWanMbus43Value27		OBJECT-TYPE
			SYNTAX	INTEGER
			MAX-ACCESS	read-only
			STATUS	current
			::= { hmWanMbus43 85 }

hmWanMbus43VIF28		OBJECT-TYPE
			SYNTAX	INTEGER
			MAX-ACCESS	read-only
			STATUS	current
			::= { hmWanMbus43 86 }

hmWanMbus43Value28		OBJECT-TYPE
			SYNTAX	INTEGER
			MAX-ACCESS	read-only
			STATUS	current
			::= { hmWanMbus43 87 }

hmWanMbus43VIF29		OBJECT-TYPE
			SYNTAX	INTEGER
			MAX-ACCESS	read-only
			STATUS	current
			::= { hmWanMbus43 88 }

hmWanMbus43Value29		OBJECT-TYPE
			SYNTAX	INTEGER
			MAX-ACCESS	read-only
			STATUS	current
			::= { hmWanMbus43 89 }

hmWanMbus43VIF2A		OBJECT-TYPE
			SYNTAX	INTEGER
			MAX-ACCESS	read-only
			STATUS	current
			::= { hmWanMbus43 90 }

hmWanMbus43Value2A		OBJECT-TYPE
			SYNTAX	INTEGER
			MAX-ACCESS	read-only
			STATUS	current
			::= { hmWanMbus43 91 }

hmWanMbus43VIF2B		OBJECT-TYPE
			SYNTAX	INTEGER
			MAX-ACCESS	read-only
			STATUS	current
			::= { hmWanMbus43 92 }

hmWanMbus43Value2B		OBJECT-TYPE
			SYNTAX	INTEGER
			MAX-ACCESS	read-only
			STATUS	current
			::= { hmWanMbus43 93 }

hmWanMbus43VIF2C		OBJECT-TYPE
			SYNTAX	INTEGER
			MAX-ACCESS	read-only
			STATUS	current
			::= { hmWanMbus43 94 }

hmWanMbus43Value2C		OBJECT-TYPE
			SYNTAX	INTEGER
			MAX-ACCESS	read-only
			STATUS	current
			::= { hmWanMbus43 95 }

hmWanMbus43VIF2D		OBJECT-TYPE
			SYNTAX	INTEGER
			MAX-ACCESS	read-only
			STATUS	current
			::= { hmWanMbus43 96 }

hmWanMbus43Value2D		OBJECT-TYPE
			SYNTAX	INTEGER
			MAX-ACCESS	read-only
			STATUS	current
			::= { hmWanMbus43 97 }

hmWanMbus43VIF2E		OBJECT-TYPE
			SYNTAX	INTEGER
			MAX-ACCESS	read-only
			STATUS	current
			::= { hmWanMbus43 98 }

hmWanMbus43Value2E		OBJECT-TYPE
			SYNTAX	INTEGER
			MAX-ACCESS	read-only
			STATUS	current
			::= { hmWanMbus43 99 }

hmWanMbus43VIF2F		OBJECT-TYPE
			SYNTAX	INTEGER
			MAX-ACCESS	read-only
			STATUS	current
			::= { hmWanMbus43 100 }

hmWanMbus43Value2F		OBJECT-TYPE
			SYNTAX	INTEGER
			MAX-ACCESS	read-only
			STATUS	current
			::= { hmWanMbus43 101 }

hmWanMbus44			OBJECT IDENTIFIER ::= { hmWanMbus 68 }

hmWanMbus44IdNumber		OBJECT-TYPE
			SYNTAX	Gauge32
			MAX-ACCESS	read-only
			STATUS	current
			::= { hmWanMbus44 1 }

hmWanMbus44Manufacturer	OBJECT-TYPE
			SYNTAX	Gauge32
			MAX-ACCESS	read-only
			STATUS	current
			::= { hmWanMbus44 2 }

hmWanMbus44Version		OBJECT-TYPE
			SYNTAX	Gauge32
			MAX-ACCESS	read-only
			STATUS	current
			::= { hmWanMbus44 3 }

hmWanMbus44Medium		OBJECT-TYPE
			SYNTAX	Gauge32
			MAX-ACCESS	read-only
			STATUS	current
			::= { hmWanMbus44 4 }

hmWanMbus44Status		OBJECT-TYPE
			SYNTAX	Gauge32
			MAX-ACCESS	read-only
			STATUS	current
			::= { hmWanMbus44 5 }

hmWanMbus44VIF00		OBJECT-TYPE
			SYNTAX	INTEGER
			MAX-ACCESS	read-only
			STATUS	current
			::= { hmWanMbus44 6 }

hmWanMbus44Value00		OBJECT-TYPE
			SYNTAX	INTEGER
			MAX-ACCESS	read-only
			STATUS	current
			::= { hmWanMbus44 7 }

hmWanMbus44VIF01		OBJECT-TYPE
			SYNTAX	INTEGER
			MAX-ACCESS	read-only
			STATUS	current
			::= { hmWanMbus44 8 }

hmWanMbus44Value01		OBJECT-TYPE
			SYNTAX	INTEGER
			MAX-ACCESS	read-only
			STATUS	current
			::= { hmWanMbus44 9 }

hmWanMbus44VIF02		OBJECT-TYPE
			SYNTAX	INTEGER
			MAX-ACCESS	read-only
			STATUS	current
			::= { hmWanMbus44 10 }

hmWanMbus44Value02		OBJECT-TYPE
			SYNTAX	INTEGER
			MAX-ACCESS	read-only
			STATUS	current
			::= { hmWanMbus44 11 }

hmWanMbus44VIF03		OBJECT-TYPE
			SYNTAX	INTEGER
			MAX-ACCESS	read-only
			STATUS	current
			::= { hmWanMbus44 12 }

hmWanMbus44Value03		OBJECT-TYPE
			SYNTAX	INTEGER
			MAX-ACCESS	read-only
			STATUS	current
			::= { hmWanMbus44 13 }

hmWanMbus44VIF04		OBJECT-TYPE
			SYNTAX	INTEGER
			MAX-ACCESS	read-only
			STATUS	current
			::= { hmWanMbus44 14 }

hmWanMbus44Value04		OBJECT-TYPE
			SYNTAX	INTEGER
			MAX-ACCESS	read-only
			STATUS	current
			::= { hmWanMbus44 15 }

hmWanMbus44VIF05		OBJECT-TYPE
			SYNTAX	INTEGER
			MAX-ACCESS	read-only
			STATUS	current
			::= { hmWanMbus44 16 }

hmWanMbus44Value05		OBJECT-TYPE
			SYNTAX	INTEGER
			MAX-ACCESS	read-only
			STATUS	current
			::= { hmWanMbus44 17 }

hmWanMbus44VIF06		OBJECT-TYPE
			SYNTAX	INTEGER
			MAX-ACCESS	read-only
			STATUS	current
			::= { hmWanMbus44 18 }

hmWanMbus44Value06		OBJECT-TYPE
			SYNTAX	INTEGER
			MAX-ACCESS	read-only
			STATUS	current
			::= { hmWanMbus44 19 }

hmWanMbus44VIF07		OBJECT-TYPE
			SYNTAX	INTEGER
			MAX-ACCESS	read-only
			STATUS	current
			::= { hmWanMbus44 20 }

hmWanMbus44Value07		OBJECT-TYPE
			SYNTAX	INTEGER
			MAX-ACCESS	read-only
			STATUS	current
			::= { hmWanMbus44 21 }

hmWanMbus44VIF08		OBJECT-TYPE
			SYNTAX	INTEGER
			MAX-ACCESS	read-only
			STATUS	current
			::= { hmWanMbus44 22 }

hmWanMbus44Value08		OBJECT-TYPE
			SYNTAX	INTEGER
			MAX-ACCESS	read-only
			STATUS	current
			::= { hmWanMbus44 23 }

hmWanMbus44VIF09		OBJECT-TYPE
			SYNTAX	INTEGER
			MAX-ACCESS	read-only
			STATUS	current
			::= { hmWanMbus44 24 }

hmWanMbus44Value09		OBJECT-TYPE
			SYNTAX	INTEGER
			MAX-ACCESS	read-only
			STATUS	current
			::= { hmWanMbus44 25 }

hmWanMbus44VIF0A		OBJECT-TYPE
			SYNTAX	INTEGER
			MAX-ACCESS	read-only
			STATUS	current
			::= { hmWanMbus44 26 }

hmWanMbus44Value0A		OBJECT-TYPE
			SYNTAX	INTEGER
			MAX-ACCESS	read-only
			STATUS	current
			::= { hmWanMbus44 27 }

hmWanMbus44VIF0B		OBJECT-TYPE
			SYNTAX	INTEGER
			MAX-ACCESS	read-only
			STATUS	current
			::= { hmWanMbus44 28 }

hmWanMbus44Value0B		OBJECT-TYPE
			SYNTAX	INTEGER
			MAX-ACCESS	read-only
			STATUS	current
			::= { hmWanMbus44 29 }

hmWanMbus44VIF0C		OBJECT-TYPE
			SYNTAX	INTEGER
			MAX-ACCESS	read-only
			STATUS	current
			::= { hmWanMbus44 30 }

hmWanMbus44Value0C		OBJECT-TYPE
			SYNTAX	INTEGER
			MAX-ACCESS	read-only
			STATUS	current
			::= { hmWanMbus44 31 }

hmWanMbus44VIF0D		OBJECT-TYPE
			SYNTAX	INTEGER
			MAX-ACCESS	read-only
			STATUS	current
			::= { hmWanMbus44 32 }

hmWanMbus44Value0D		OBJECT-TYPE
			SYNTAX	INTEGER
			MAX-ACCESS	read-only
			STATUS	current
			::= { hmWanMbus44 33 }

hmWanMbus44VIF0E		OBJECT-TYPE
			SYNTAX	INTEGER
			MAX-ACCESS	read-only
			STATUS	current
			::= { hmWanMbus44 34 }

hmWanMbus44Value0E		OBJECT-TYPE
			SYNTAX	INTEGER
			MAX-ACCESS	read-only
			STATUS	current
			::= { hmWanMbus44 35 }

hmWanMbus44VIF0F		OBJECT-TYPE
			SYNTAX	INTEGER
			MAX-ACCESS	read-only
			STATUS	current
			::= { hmWanMbus44 36 }

hmWanMbus44Value0F		OBJECT-TYPE
			SYNTAX	INTEGER
			MAX-ACCESS	read-only
			STATUS	current
			::= { hmWanMbus44 37 }

hmWanMbus44VIF10		OBJECT-TYPE
			SYNTAX	INTEGER
			MAX-ACCESS	read-only
			STATUS	current
			::= { hmWanMbus44 38 }

hmWanMbus44Value10		OBJECT-TYPE
			SYNTAX	INTEGER
			MAX-ACCESS	read-only
			STATUS	current
			::= { hmWanMbus44 39 }

hmWanMbus44VIF11		OBJECT-TYPE
			SYNTAX	INTEGER
			MAX-ACCESS	read-only
			STATUS	current
			::= { hmWanMbus44 40 }

hmWanMbus44Value11		OBJECT-TYPE
			SYNTAX	INTEGER
			MAX-ACCESS	read-only
			STATUS	current
			::= { hmWanMbus44 41 }

hmWanMbus44VIF12		OBJECT-TYPE
			SYNTAX	INTEGER
			MAX-ACCESS	read-only
			STATUS	current
			::= { hmWanMbus44 42 }

hmWanMbus44Value12		OBJECT-TYPE
			SYNTAX	INTEGER
			MAX-ACCESS	read-only
			STATUS	current
			::= { hmWanMbus44 43 }

hmWanMbus44VIF13		OBJECT-TYPE
			SYNTAX	INTEGER
			MAX-ACCESS	read-only
			STATUS	current
			::= { hmWanMbus44 44 }

hmWanMbus44Value13		OBJECT-TYPE
			SYNTAX	INTEGER
			MAX-ACCESS	read-only
			STATUS	current
			::= { hmWanMbus44 45 }

hmWanMbus44VIF14		OBJECT-TYPE
			SYNTAX	INTEGER
			MAX-ACCESS	read-only
			STATUS	current
			::= { hmWanMbus44 46 }

hmWanMbus44Value14		OBJECT-TYPE
			SYNTAX	INTEGER
			MAX-ACCESS	read-only
			STATUS	current
			::= { hmWanMbus44 47 }

hmWanMbus44VIF15		OBJECT-TYPE
			SYNTAX	INTEGER
			MAX-ACCESS	read-only
			STATUS	current
			::= { hmWanMbus44 48 }

hmWanMbus44Value15		OBJECT-TYPE
			SYNTAX	INTEGER
			MAX-ACCESS	read-only
			STATUS	current
			::= { hmWanMbus44 49 }

hmWanMbus44VIF16		OBJECT-TYPE
			SYNTAX	INTEGER
			MAX-ACCESS	read-only
			STATUS	current
			::= { hmWanMbus44 50 }

hmWanMbus44Value16		OBJECT-TYPE
			SYNTAX	INTEGER
			MAX-ACCESS	read-only
			STATUS	current
			::= { hmWanMbus44 51 }

hmWanMbus44VIF17		OBJECT-TYPE
			SYNTAX	INTEGER
			MAX-ACCESS	read-only
			STATUS	current
			::= { hmWanMbus44 52 }

hmWanMbus44Value17		OBJECT-TYPE
			SYNTAX	INTEGER
			MAX-ACCESS	read-only
			STATUS	current
			::= { hmWanMbus44 53 }

hmWanMbus44VIF18		OBJECT-TYPE
			SYNTAX	INTEGER
			MAX-ACCESS	read-only
			STATUS	current
			::= { hmWanMbus44 54 }

hmWanMbus44Value18		OBJECT-TYPE
			SYNTAX	INTEGER
			MAX-ACCESS	read-only
			STATUS	current
			::= { hmWanMbus44 55 }

hmWanMbus44VIF19		OBJECT-TYPE
			SYNTAX	INTEGER
			MAX-ACCESS	read-only
			STATUS	current
			::= { hmWanMbus44 56 }

hmWanMbus44Value19		OBJECT-TYPE
			SYNTAX	INTEGER
			MAX-ACCESS	read-only
			STATUS	current
			::= { hmWanMbus44 57 }

hmWanMbus44VIF1A		OBJECT-TYPE
			SYNTAX	INTEGER
			MAX-ACCESS	read-only
			STATUS	current
			::= { hmWanMbus44 58 }

hmWanMbus44Value1A		OBJECT-TYPE
			SYNTAX	INTEGER
			MAX-ACCESS	read-only
			STATUS	current
			::= { hmWanMbus44 59 }

hmWanMbus44VIF1B		OBJECT-TYPE
			SYNTAX	INTEGER
			MAX-ACCESS	read-only
			STATUS	current
			::= { hmWanMbus44 60 }

hmWanMbus44Value1B		OBJECT-TYPE
			SYNTAX	INTEGER
			MAX-ACCESS	read-only
			STATUS	current
			::= { hmWanMbus44 61 }

hmWanMbus44VIF1C		OBJECT-TYPE
			SYNTAX	INTEGER
			MAX-ACCESS	read-only
			STATUS	current
			::= { hmWanMbus44 62 }

hmWanMbus44Value1C		OBJECT-TYPE
			SYNTAX	INTEGER
			MAX-ACCESS	read-only
			STATUS	current
			::= { hmWanMbus44 63 }

hmWanMbus44VIF1D		OBJECT-TYPE
			SYNTAX	INTEGER
			MAX-ACCESS	read-only
			STATUS	current
			::= { hmWanMbus44 64 }

hmWanMbus44Value1D		OBJECT-TYPE
			SYNTAX	INTEGER
			MAX-ACCESS	read-only
			STATUS	current
			::= { hmWanMbus44 65 }

hmWanMbus44VIF1E		OBJECT-TYPE
			SYNTAX	INTEGER
			MAX-ACCESS	read-only
			STATUS	current
			::= { hmWanMbus44 66 }

hmWanMbus44Value1E		OBJECT-TYPE
			SYNTAX	INTEGER
			MAX-ACCESS	read-only
			STATUS	current
			::= { hmWanMbus44 67 }

hmWanMbus44VIF1F		OBJECT-TYPE
			SYNTAX	INTEGER
			MAX-ACCESS	read-only
			STATUS	current
			::= { hmWanMbus44 68 }

hmWanMbus44Value1F		OBJECT-TYPE
			SYNTAX	INTEGER
			MAX-ACCESS	read-only
			STATUS	current
			::= { hmWanMbus44 69 }

hmWanMbus44VIF20		OBJECT-TYPE
			SYNTAX	INTEGER
			MAX-ACCESS	read-only
			STATUS	current
			::= { hmWanMbus44 70 }

hmWanMbus44Value20		OBJECT-TYPE
			SYNTAX	INTEGER
			MAX-ACCESS	read-only
			STATUS	current
			::= { hmWanMbus44 71 }

hmWanMbus44VIF21		OBJECT-TYPE
			SYNTAX	INTEGER
			MAX-ACCESS	read-only
			STATUS	current
			::= { hmWanMbus44 72 }

hmWanMbus44Value21		OBJECT-TYPE
			SYNTAX	INTEGER
			MAX-ACCESS	read-only
			STATUS	current
			::= { hmWanMbus44 73 }

hmWanMbus44VIF22		OBJECT-TYPE
			SYNTAX	INTEGER
			MAX-ACCESS	read-only
			STATUS	current
			::= { hmWanMbus44 74 }

hmWanMbus44Value22		OBJECT-TYPE
			SYNTAX	INTEGER
			MAX-ACCESS	read-only
			STATUS	current
			::= { hmWanMbus44 75 }

hmWanMbus44VIF23		OBJECT-TYPE
			SYNTAX	INTEGER
			MAX-ACCESS	read-only
			STATUS	current
			::= { hmWanMbus44 76 }

hmWanMbus44Value23		OBJECT-TYPE
			SYNTAX	INTEGER
			MAX-ACCESS	read-only
			STATUS	current
			::= { hmWanMbus44 77 }

hmWanMbus44VIF24		OBJECT-TYPE
			SYNTAX	INTEGER
			MAX-ACCESS	read-only
			STATUS	current
			::= { hmWanMbus44 78 }

hmWanMbus44Value24		OBJECT-TYPE
			SYNTAX	INTEGER
			MAX-ACCESS	read-only
			STATUS	current
			::= { hmWanMbus44 79 }

hmWanMbus44VIF25		OBJECT-TYPE
			SYNTAX	INTEGER
			MAX-ACCESS	read-only
			STATUS	current
			::= { hmWanMbus44 80 }

hmWanMbus44Value25		OBJECT-TYPE
			SYNTAX	INTEGER
			MAX-ACCESS	read-only
			STATUS	current
			::= { hmWanMbus44 81 }

hmWanMbus44VIF26		OBJECT-TYPE
			SYNTAX	INTEGER
			MAX-ACCESS	read-only
			STATUS	current
			::= { hmWanMbus44 82 }

hmWanMbus44Value26		OBJECT-TYPE
			SYNTAX	INTEGER
			MAX-ACCESS	read-only
			STATUS	current
			::= { hmWanMbus44 83 }

hmWanMbus44VIF27		OBJECT-TYPE
			SYNTAX	INTEGER
			MAX-ACCESS	read-only
			STATUS	current
			::= { hmWanMbus44 84 }

hmWanMbus44Value27		OBJECT-TYPE
			SYNTAX	INTEGER
			MAX-ACCESS	read-only
			STATUS	current
			::= { hmWanMbus44 85 }

hmWanMbus44VIF28		OBJECT-TYPE
			SYNTAX	INTEGER
			MAX-ACCESS	read-only
			STATUS	current
			::= { hmWanMbus44 86 }

hmWanMbus44Value28		OBJECT-TYPE
			SYNTAX	INTEGER
			MAX-ACCESS	read-only
			STATUS	current
			::= { hmWanMbus44 87 }

hmWanMbus44VIF29		OBJECT-TYPE
			SYNTAX	INTEGER
			MAX-ACCESS	read-only
			STATUS	current
			::= { hmWanMbus44 88 }

hmWanMbus44Value29		OBJECT-TYPE
			SYNTAX	INTEGER
			MAX-ACCESS	read-only
			STATUS	current
			::= { hmWanMbus44 89 }

hmWanMbus44VIF2A		OBJECT-TYPE
			SYNTAX	INTEGER
			MAX-ACCESS	read-only
			STATUS	current
			::= { hmWanMbus44 90 }

hmWanMbus44Value2A		OBJECT-TYPE
			SYNTAX	INTEGER
			MAX-ACCESS	read-only
			STATUS	current
			::= { hmWanMbus44 91 }

hmWanMbus44VIF2B		OBJECT-TYPE
			SYNTAX	INTEGER
			MAX-ACCESS	read-only
			STATUS	current
			::= { hmWanMbus44 92 }

hmWanMbus44Value2B		OBJECT-TYPE
			SYNTAX	INTEGER
			MAX-ACCESS	read-only
			STATUS	current
			::= { hmWanMbus44 93 }

hmWanMbus44VIF2C		OBJECT-TYPE
			SYNTAX	INTEGER
			MAX-ACCESS	read-only
			STATUS	current
			::= { hmWanMbus44 94 }

hmWanMbus44Value2C		OBJECT-TYPE
			SYNTAX	INTEGER
			MAX-ACCESS	read-only
			STATUS	current
			::= { hmWanMbus44 95 }

hmWanMbus44VIF2D		OBJECT-TYPE
			SYNTAX	INTEGER
			MAX-ACCESS	read-only
			STATUS	current
			::= { hmWanMbus44 96 }

hmWanMbus44Value2D		OBJECT-TYPE
			SYNTAX	INTEGER
			MAX-ACCESS	read-only
			STATUS	current
			::= { hmWanMbus44 97 }

hmWanMbus44VIF2E		OBJECT-TYPE
			SYNTAX	INTEGER
			MAX-ACCESS	read-only
			STATUS	current
			::= { hmWanMbus44 98 }

hmWanMbus44Value2E		OBJECT-TYPE
			SYNTAX	INTEGER
			MAX-ACCESS	read-only
			STATUS	current
			::= { hmWanMbus44 99 }

hmWanMbus44VIF2F		OBJECT-TYPE
			SYNTAX	INTEGER
			MAX-ACCESS	read-only
			STATUS	current
			::= { hmWanMbus44 100 }

hmWanMbus44Value2F		OBJECT-TYPE
			SYNTAX	INTEGER
			MAX-ACCESS	read-only
			STATUS	current
			::= { hmWanMbus44 101 }

hmWanMbus45			OBJECT IDENTIFIER ::= { hmWanMbus 69 }

hmWanMbus45IdNumber		OBJECT-TYPE
			SYNTAX	Gauge32
			MAX-ACCESS	read-only
			STATUS	current
			::= { hmWanMbus45 1 }

hmWanMbus45Manufacturer	OBJECT-TYPE
			SYNTAX	Gauge32
			MAX-ACCESS	read-only
			STATUS	current
			::= { hmWanMbus45 2 }

hmWanMbus45Version		OBJECT-TYPE
			SYNTAX	Gauge32
			MAX-ACCESS	read-only
			STATUS	current
			::= { hmWanMbus45 3 }

hmWanMbus45Medium		OBJECT-TYPE
			SYNTAX	Gauge32
			MAX-ACCESS	read-only
			STATUS	current
			::= { hmWanMbus45 4 }

hmWanMbus45Status		OBJECT-TYPE
			SYNTAX	Gauge32
			MAX-ACCESS	read-only
			STATUS	current
			::= { hmWanMbus45 5 }

hmWanMbus45VIF00		OBJECT-TYPE
			SYNTAX	INTEGER
			MAX-ACCESS	read-only
			STATUS	current
			::= { hmWanMbus45 6 }

hmWanMbus45Value00		OBJECT-TYPE
			SYNTAX	INTEGER
			MAX-ACCESS	read-only
			STATUS	current
			::= { hmWanMbus45 7 }

hmWanMbus45VIF01		OBJECT-TYPE
			SYNTAX	INTEGER
			MAX-ACCESS	read-only
			STATUS	current
			::= { hmWanMbus45 8 }

hmWanMbus45Value01		OBJECT-TYPE
			SYNTAX	INTEGER
			MAX-ACCESS	read-only
			STATUS	current
			::= { hmWanMbus45 9 }

hmWanMbus45VIF02		OBJECT-TYPE
			SYNTAX	INTEGER
			MAX-ACCESS	read-only
			STATUS	current
			::= { hmWanMbus45 10 }

hmWanMbus45Value02		OBJECT-TYPE
			SYNTAX	INTEGER
			MAX-ACCESS	read-only
			STATUS	current
			::= { hmWanMbus45 11 }

hmWanMbus45VIF03		OBJECT-TYPE
			SYNTAX	INTEGER
			MAX-ACCESS	read-only
			STATUS	current
			::= { hmWanMbus45 12 }

hmWanMbus45Value03		OBJECT-TYPE
			SYNTAX	INTEGER
			MAX-ACCESS	read-only
			STATUS	current
			::= { hmWanMbus45 13 }

hmWanMbus45VIF04		OBJECT-TYPE
			SYNTAX	INTEGER
			MAX-ACCESS	read-only
			STATUS	current
			::= { hmWanMbus45 14 }

hmWanMbus45Value04		OBJECT-TYPE
			SYNTAX	INTEGER
			MAX-ACCESS	read-only
			STATUS	current
			::= { hmWanMbus45 15 }

hmWanMbus45VIF05		OBJECT-TYPE
			SYNTAX	INTEGER
			MAX-ACCESS	read-only
			STATUS	current
			::= { hmWanMbus45 16 }

hmWanMbus45Value05		OBJECT-TYPE
			SYNTAX	INTEGER
			MAX-ACCESS	read-only
			STATUS	current
			::= { hmWanMbus45 17 }

hmWanMbus45VIF06		OBJECT-TYPE
			SYNTAX	INTEGER
			MAX-ACCESS	read-only
			STATUS	current
			::= { hmWanMbus45 18 }

hmWanMbus45Value06		OBJECT-TYPE
			SYNTAX	INTEGER
			MAX-ACCESS	read-only
			STATUS	current
			::= { hmWanMbus45 19 }

hmWanMbus45VIF07		OBJECT-TYPE
			SYNTAX	INTEGER
			MAX-ACCESS	read-only
			STATUS	current
			::= { hmWanMbus45 20 }

hmWanMbus45Value07		OBJECT-TYPE
			SYNTAX	INTEGER
			MAX-ACCESS	read-only
			STATUS	current
			::= { hmWanMbus45 21 }

hmWanMbus45VIF08		OBJECT-TYPE
			SYNTAX	INTEGER
			MAX-ACCESS	read-only
			STATUS	current
			::= { hmWanMbus45 22 }

hmWanMbus45Value08		OBJECT-TYPE
			SYNTAX	INTEGER
			MAX-ACCESS	read-only
			STATUS	current
			::= { hmWanMbus45 23 }

hmWanMbus45VIF09		OBJECT-TYPE
			SYNTAX	INTEGER
			MAX-ACCESS	read-only
			STATUS	current
			::= { hmWanMbus45 24 }

hmWanMbus45Value09		OBJECT-TYPE
			SYNTAX	INTEGER
			MAX-ACCESS	read-only
			STATUS	current
			::= { hmWanMbus45 25 }

hmWanMbus45VIF0A		OBJECT-TYPE
			SYNTAX	INTEGER
			MAX-ACCESS	read-only
			STATUS	current
			::= { hmWanMbus45 26 }

hmWanMbus45Value0A		OBJECT-TYPE
			SYNTAX	INTEGER
			MAX-ACCESS	read-only
			STATUS	current
			::= { hmWanMbus45 27 }

hmWanMbus45VIF0B		OBJECT-TYPE
			SYNTAX	INTEGER
			MAX-ACCESS	read-only
			STATUS	current
			::= { hmWanMbus45 28 }

hmWanMbus45Value0B		OBJECT-TYPE
			SYNTAX	INTEGER
			MAX-ACCESS	read-only
			STATUS	current
			::= { hmWanMbus45 29 }

hmWanMbus45VIF0C		OBJECT-TYPE
			SYNTAX	INTEGER
			MAX-ACCESS	read-only
			STATUS	current
			::= { hmWanMbus45 30 }

hmWanMbus45Value0C		OBJECT-TYPE
			SYNTAX	INTEGER
			MAX-ACCESS	read-only
			STATUS	current
			::= { hmWanMbus45 31 }

hmWanMbus45VIF0D		OBJECT-TYPE
			SYNTAX	INTEGER
			MAX-ACCESS	read-only
			STATUS	current
			::= { hmWanMbus45 32 }

hmWanMbus45Value0D		OBJECT-TYPE
			SYNTAX	INTEGER
			MAX-ACCESS	read-only
			STATUS	current
			::= { hmWanMbus45 33 }

hmWanMbus45VIF0E		OBJECT-TYPE
			SYNTAX	INTEGER
			MAX-ACCESS	read-only
			STATUS	current
			::= { hmWanMbus45 34 }

hmWanMbus45Value0E		OBJECT-TYPE
			SYNTAX	INTEGER
			MAX-ACCESS	read-only
			STATUS	current
			::= { hmWanMbus45 35 }

hmWanMbus45VIF0F		OBJECT-TYPE
			SYNTAX	INTEGER
			MAX-ACCESS	read-only
			STATUS	current
			::= { hmWanMbus45 36 }

hmWanMbus45Value0F		OBJECT-TYPE
			SYNTAX	INTEGER
			MAX-ACCESS	read-only
			STATUS	current
			::= { hmWanMbus45 37 }

hmWanMbus45VIF10		OBJECT-TYPE
			SYNTAX	INTEGER
			MAX-ACCESS	read-only
			STATUS	current
			::= { hmWanMbus45 38 }

hmWanMbus45Value10		OBJECT-TYPE
			SYNTAX	INTEGER
			MAX-ACCESS	read-only
			STATUS	current
			::= { hmWanMbus45 39 }

hmWanMbus45VIF11		OBJECT-TYPE
			SYNTAX	INTEGER
			MAX-ACCESS	read-only
			STATUS	current
			::= { hmWanMbus45 40 }

hmWanMbus45Value11		OBJECT-TYPE
			SYNTAX	INTEGER
			MAX-ACCESS	read-only
			STATUS	current
			::= { hmWanMbus45 41 }

hmWanMbus45VIF12		OBJECT-TYPE
			SYNTAX	INTEGER
			MAX-ACCESS	read-only
			STATUS	current
			::= { hmWanMbus45 42 }

hmWanMbus45Value12		OBJECT-TYPE
			SYNTAX	INTEGER
			MAX-ACCESS	read-only
			STATUS	current
			::= { hmWanMbus45 43 }

hmWanMbus45VIF13		OBJECT-TYPE
			SYNTAX	INTEGER
			MAX-ACCESS	read-only
			STATUS	current
			::= { hmWanMbus45 44 }

hmWanMbus45Value13		OBJECT-TYPE
			SYNTAX	INTEGER
			MAX-ACCESS	read-only
			STATUS	current
			::= { hmWanMbus45 45 }

hmWanMbus45VIF14		OBJECT-TYPE
			SYNTAX	INTEGER
			MAX-ACCESS	read-only
			STATUS	current
			::= { hmWanMbus45 46 }

hmWanMbus45Value14		OBJECT-TYPE
			SYNTAX	INTEGER
			MAX-ACCESS	read-only
			STATUS	current
			::= { hmWanMbus45 47 }

hmWanMbus45VIF15		OBJECT-TYPE
			SYNTAX	INTEGER
			MAX-ACCESS	read-only
			STATUS	current
			::= { hmWanMbus45 48 }

hmWanMbus45Value15		OBJECT-TYPE
			SYNTAX	INTEGER
			MAX-ACCESS	read-only
			STATUS	current
			::= { hmWanMbus45 49 }

hmWanMbus45VIF16		OBJECT-TYPE
			SYNTAX	INTEGER
			MAX-ACCESS	read-only
			STATUS	current
			::= { hmWanMbus45 50 }

hmWanMbus45Value16		OBJECT-TYPE
			SYNTAX	INTEGER
			MAX-ACCESS	read-only
			STATUS	current
			::= { hmWanMbus45 51 }

hmWanMbus45VIF17		OBJECT-TYPE
			SYNTAX	INTEGER
			MAX-ACCESS	read-only
			STATUS	current
			::= { hmWanMbus45 52 }

hmWanMbus45Value17		OBJECT-TYPE
			SYNTAX	INTEGER
			MAX-ACCESS	read-only
			STATUS	current
			::= { hmWanMbus45 53 }

hmWanMbus45VIF18		OBJECT-TYPE
			SYNTAX	INTEGER
			MAX-ACCESS	read-only
			STATUS	current
			::= { hmWanMbus45 54 }

hmWanMbus45Value18		OBJECT-TYPE
			SYNTAX	INTEGER
			MAX-ACCESS	read-only
			STATUS	current
			::= { hmWanMbus45 55 }

hmWanMbus45VIF19		OBJECT-TYPE
			SYNTAX	INTEGER
			MAX-ACCESS	read-only
			STATUS	current
			::= { hmWanMbus45 56 }

hmWanMbus45Value19		OBJECT-TYPE
			SYNTAX	INTEGER
			MAX-ACCESS	read-only
			STATUS	current
			::= { hmWanMbus45 57 }

hmWanMbus45VIF1A		OBJECT-TYPE
			SYNTAX	INTEGER
			MAX-ACCESS	read-only
			STATUS	current
			::= { hmWanMbus45 58 }

hmWanMbus45Value1A		OBJECT-TYPE
			SYNTAX	INTEGER
			MAX-ACCESS	read-only
			STATUS	current
			::= { hmWanMbus45 59 }

hmWanMbus45VIF1B		OBJECT-TYPE
			SYNTAX	INTEGER
			MAX-ACCESS	read-only
			STATUS	current
			::= { hmWanMbus45 60 }

hmWanMbus45Value1B		OBJECT-TYPE
			SYNTAX	INTEGER
			MAX-ACCESS	read-only
			STATUS	current
			::= { hmWanMbus45 61 }

hmWanMbus45VIF1C		OBJECT-TYPE
			SYNTAX	INTEGER
			MAX-ACCESS	read-only
			STATUS	current
			::= { hmWanMbus45 62 }

hmWanMbus45Value1C		OBJECT-TYPE
			SYNTAX	INTEGER
			MAX-ACCESS	read-only
			STATUS	current
			::= { hmWanMbus45 63 }

hmWanMbus45VIF1D		OBJECT-TYPE
			SYNTAX	INTEGER
			MAX-ACCESS	read-only
			STATUS	current
			::= { hmWanMbus45 64 }

hmWanMbus45Value1D		OBJECT-TYPE
			SYNTAX	INTEGER
			MAX-ACCESS	read-only
			STATUS	current
			::= { hmWanMbus45 65 }

hmWanMbus45VIF1E		OBJECT-TYPE
			SYNTAX	INTEGER
			MAX-ACCESS	read-only
			STATUS	current
			::= { hmWanMbus45 66 }

hmWanMbus45Value1E		OBJECT-TYPE
			SYNTAX	INTEGER
			MAX-ACCESS	read-only
			STATUS	current
			::= { hmWanMbus45 67 }

hmWanMbus45VIF1F		OBJECT-TYPE
			SYNTAX	INTEGER
			MAX-ACCESS	read-only
			STATUS	current
			::= { hmWanMbus45 68 }

hmWanMbus45Value1F		OBJECT-TYPE
			SYNTAX	INTEGER
			MAX-ACCESS	read-only
			STATUS	current
			::= { hmWanMbus45 69 }

hmWanMbus45VIF20		OBJECT-TYPE
			SYNTAX	INTEGER
			MAX-ACCESS	read-only
			STATUS	current
			::= { hmWanMbus45 70 }

hmWanMbus45Value20		OBJECT-TYPE
			SYNTAX	INTEGER
			MAX-ACCESS	read-only
			STATUS	current
			::= { hmWanMbus45 71 }

hmWanMbus45VIF21		OBJECT-TYPE
			SYNTAX	INTEGER
			MAX-ACCESS	read-only
			STATUS	current
			::= { hmWanMbus45 72 }

hmWanMbus45Value21		OBJECT-TYPE
			SYNTAX	INTEGER
			MAX-ACCESS	read-only
			STATUS	current
			::= { hmWanMbus45 73 }

hmWanMbus45VIF22		OBJECT-TYPE
			SYNTAX	INTEGER
			MAX-ACCESS	read-only
			STATUS	current
			::= { hmWanMbus45 74 }

hmWanMbus45Value22		OBJECT-TYPE
			SYNTAX	INTEGER
			MAX-ACCESS	read-only
			STATUS	current
			::= { hmWanMbus45 75 }

hmWanMbus45VIF23		OBJECT-TYPE
			SYNTAX	INTEGER
			MAX-ACCESS	read-only
			STATUS	current
			::= { hmWanMbus45 76 }

hmWanMbus45Value23		OBJECT-TYPE
			SYNTAX	INTEGER
			MAX-ACCESS	read-only
			STATUS	current
			::= { hmWanMbus45 77 }

hmWanMbus45VIF24		OBJECT-TYPE
			SYNTAX	INTEGER
			MAX-ACCESS	read-only
			STATUS	current
			::= { hmWanMbus45 78 }

hmWanMbus45Value24		OBJECT-TYPE
			SYNTAX	INTEGER
			MAX-ACCESS	read-only
			STATUS	current
			::= { hmWanMbus45 79 }

hmWanMbus45VIF25		OBJECT-TYPE
			SYNTAX	INTEGER
			MAX-ACCESS	read-only
			STATUS	current
			::= { hmWanMbus45 80 }

hmWanMbus45Value25		OBJECT-TYPE
			SYNTAX	INTEGER
			MAX-ACCESS	read-only
			STATUS	current
			::= { hmWanMbus45 81 }

hmWanMbus45VIF26		OBJECT-TYPE
			SYNTAX	INTEGER
			MAX-ACCESS	read-only
			STATUS	current
			::= { hmWanMbus45 82 }

hmWanMbus45Value26		OBJECT-TYPE
			SYNTAX	INTEGER
			MAX-ACCESS	read-only
			STATUS	current
			::= { hmWanMbus45 83 }

hmWanMbus45VIF27		OBJECT-TYPE
			SYNTAX	INTEGER
			MAX-ACCESS	read-only
			STATUS	current
			::= { hmWanMbus45 84 }

hmWanMbus45Value27		OBJECT-TYPE
			SYNTAX	INTEGER
			MAX-ACCESS	read-only
			STATUS	current
			::= { hmWanMbus45 85 }

hmWanMbus45VIF28		OBJECT-TYPE
			SYNTAX	INTEGER
			MAX-ACCESS	read-only
			STATUS	current
			::= { hmWanMbus45 86 }

hmWanMbus45Value28		OBJECT-TYPE
			SYNTAX	INTEGER
			MAX-ACCESS	read-only
			STATUS	current
			::= { hmWanMbus45 87 }

hmWanMbus45VIF29		OBJECT-TYPE
			SYNTAX	INTEGER
			MAX-ACCESS	read-only
			STATUS	current
			::= { hmWanMbus45 88 }

hmWanMbus45Value29		OBJECT-TYPE
			SYNTAX	INTEGER
			MAX-ACCESS	read-only
			STATUS	current
			::= { hmWanMbus45 89 }

hmWanMbus45VIF2A		OBJECT-TYPE
			SYNTAX	INTEGER
			MAX-ACCESS	read-only
			STATUS	current
			::= { hmWanMbus45 90 }

hmWanMbus45Value2A		OBJECT-TYPE
			SYNTAX	INTEGER
			MAX-ACCESS	read-only
			STATUS	current
			::= { hmWanMbus45 91 }

hmWanMbus45VIF2B		OBJECT-TYPE
			SYNTAX	INTEGER
			MAX-ACCESS	read-only
			STATUS	current
			::= { hmWanMbus45 92 }

hmWanMbus45Value2B		OBJECT-TYPE
			SYNTAX	INTEGER
			MAX-ACCESS	read-only
			STATUS	current
			::= { hmWanMbus45 93 }

hmWanMbus45VIF2C		OBJECT-TYPE
			SYNTAX	INTEGER
			MAX-ACCESS	read-only
			STATUS	current
			::= { hmWanMbus45 94 }

hmWanMbus45Value2C		OBJECT-TYPE
			SYNTAX	INTEGER
			MAX-ACCESS	read-only
			STATUS	current
			::= { hmWanMbus45 95 }

hmWanMbus45VIF2D		OBJECT-TYPE
			SYNTAX	INTEGER
			MAX-ACCESS	read-only
			STATUS	current
			::= { hmWanMbus45 96 }

hmWanMbus45Value2D		OBJECT-TYPE
			SYNTAX	INTEGER
			MAX-ACCESS	read-only
			STATUS	current
			::= { hmWanMbus45 97 }

hmWanMbus45VIF2E		OBJECT-TYPE
			SYNTAX	INTEGER
			MAX-ACCESS	read-only
			STATUS	current
			::= { hmWanMbus45 98 }

hmWanMbus45Value2E		OBJECT-TYPE
			SYNTAX	INTEGER
			MAX-ACCESS	read-only
			STATUS	current
			::= { hmWanMbus45 99 }

hmWanMbus45VIF2F		OBJECT-TYPE
			SYNTAX	INTEGER
			MAX-ACCESS	read-only
			STATUS	current
			::= { hmWanMbus45 100 }

hmWanMbus45Value2F		OBJECT-TYPE
			SYNTAX	INTEGER
			MAX-ACCESS	read-only
			STATUS	current
			::= { hmWanMbus45 101 }

hmWanMbus46			OBJECT IDENTIFIER ::= { hmWanMbus 70 }

hmWanMbus46IdNumber		OBJECT-TYPE
			SYNTAX	Gauge32
			MAX-ACCESS	read-only
			STATUS	current
			::= { hmWanMbus46 1 }

hmWanMbus46Manufacturer	OBJECT-TYPE
			SYNTAX	Gauge32
			MAX-ACCESS	read-only
			STATUS	current
			::= { hmWanMbus46 2 }

hmWanMbus46Version		OBJECT-TYPE
			SYNTAX	Gauge32
			MAX-ACCESS	read-only
			STATUS	current
			::= { hmWanMbus46 3 }

hmWanMbus46Medium		OBJECT-TYPE
			SYNTAX	Gauge32
			MAX-ACCESS	read-only
			STATUS	current
			::= { hmWanMbus46 4 }

hmWanMbus46Status		OBJECT-TYPE
			SYNTAX	Gauge32
			MAX-ACCESS	read-only
			STATUS	current
			::= { hmWanMbus46 5 }

hmWanMbus46VIF00		OBJECT-TYPE
			SYNTAX	INTEGER
			MAX-ACCESS	read-only
			STATUS	current
			::= { hmWanMbus46 6 }

hmWanMbus46Value00		OBJECT-TYPE
			SYNTAX	INTEGER
			MAX-ACCESS	read-only
			STATUS	current
			::= { hmWanMbus46 7 }

hmWanMbus46VIF01		OBJECT-TYPE
			SYNTAX	INTEGER
			MAX-ACCESS	read-only
			STATUS	current
			::= { hmWanMbus46 8 }

hmWanMbus46Value01		OBJECT-TYPE
			SYNTAX	INTEGER
			MAX-ACCESS	read-only
			STATUS	current
			::= { hmWanMbus46 9 }

hmWanMbus46VIF02		OBJECT-TYPE
			SYNTAX	INTEGER
			MAX-ACCESS	read-only
			STATUS	current
			::= { hmWanMbus46 10 }

hmWanMbus46Value02		OBJECT-TYPE
			SYNTAX	INTEGER
			MAX-ACCESS	read-only
			STATUS	current
			::= { hmWanMbus46 11 }

hmWanMbus46VIF03		OBJECT-TYPE
			SYNTAX	INTEGER
			MAX-ACCESS	read-only
			STATUS	current
			::= { hmWanMbus46 12 }

hmWanMbus46Value03		OBJECT-TYPE
			SYNTAX	INTEGER
			MAX-ACCESS	read-only
			STATUS	current
			::= { hmWanMbus46 13 }

hmWanMbus46VIF04		OBJECT-TYPE
			SYNTAX	INTEGER
			MAX-ACCESS	read-only
			STATUS	current
			::= { hmWanMbus46 14 }

hmWanMbus46Value04		OBJECT-TYPE
			SYNTAX	INTEGER
			MAX-ACCESS	read-only
			STATUS	current
			::= { hmWanMbus46 15 }

hmWanMbus46VIF05		OBJECT-TYPE
			SYNTAX	INTEGER
			MAX-ACCESS	read-only
			STATUS	current
			::= { hmWanMbus46 16 }

hmWanMbus46Value05		OBJECT-TYPE
			SYNTAX	INTEGER
			MAX-ACCESS	read-only
			STATUS	current
			::= { hmWanMbus46 17 }

hmWanMbus46VIF06		OBJECT-TYPE
			SYNTAX	INTEGER
			MAX-ACCESS	read-only
			STATUS	current
			::= { hmWanMbus46 18 }

hmWanMbus46Value06		OBJECT-TYPE
			SYNTAX	INTEGER
			MAX-ACCESS	read-only
			STATUS	current
			::= { hmWanMbus46 19 }

hmWanMbus46VIF07		OBJECT-TYPE
			SYNTAX	INTEGER
			MAX-ACCESS	read-only
			STATUS	current
			::= { hmWanMbus46 20 }

hmWanMbus46Value07		OBJECT-TYPE
			SYNTAX	INTEGER
			MAX-ACCESS	read-only
			STATUS	current
			::= { hmWanMbus46 21 }

hmWanMbus46VIF08		OBJECT-TYPE
			SYNTAX	INTEGER
			MAX-ACCESS	read-only
			STATUS	current
			::= { hmWanMbus46 22 }

hmWanMbus46Value08		OBJECT-TYPE
			SYNTAX	INTEGER
			MAX-ACCESS	read-only
			STATUS	current
			::= { hmWanMbus46 23 }

hmWanMbus46VIF09		OBJECT-TYPE
			SYNTAX	INTEGER
			MAX-ACCESS	read-only
			STATUS	current
			::= { hmWanMbus46 24 }

hmWanMbus46Value09		OBJECT-TYPE
			SYNTAX	INTEGER
			MAX-ACCESS	read-only
			STATUS	current
			::= { hmWanMbus46 25 }

hmWanMbus46VIF0A		OBJECT-TYPE
			SYNTAX	INTEGER
			MAX-ACCESS	read-only
			STATUS	current
			::= { hmWanMbus46 26 }

hmWanMbus46Value0A		OBJECT-TYPE
			SYNTAX	INTEGER
			MAX-ACCESS	read-only
			STATUS	current
			::= { hmWanMbus46 27 }

hmWanMbus46VIF0B		OBJECT-TYPE
			SYNTAX	INTEGER
			MAX-ACCESS	read-only
			STATUS	current
			::= { hmWanMbus46 28 }

hmWanMbus46Value0B		OBJECT-TYPE
			SYNTAX	INTEGER
			MAX-ACCESS	read-only
			STATUS	current
			::= { hmWanMbus46 29 }

hmWanMbus46VIF0C		OBJECT-TYPE
			SYNTAX	INTEGER
			MAX-ACCESS	read-only
			STATUS	current
			::= { hmWanMbus46 30 }

hmWanMbus46Value0C		OBJECT-TYPE
			SYNTAX	INTEGER
			MAX-ACCESS	read-only
			STATUS	current
			::= { hmWanMbus46 31 }

hmWanMbus46VIF0D		OBJECT-TYPE
			SYNTAX	INTEGER
			MAX-ACCESS	read-only
			STATUS	current
			::= { hmWanMbus46 32 }

hmWanMbus46Value0D		OBJECT-TYPE
			SYNTAX	INTEGER
			MAX-ACCESS	read-only
			STATUS	current
			::= { hmWanMbus46 33 }

hmWanMbus46VIF0E		OBJECT-TYPE
			SYNTAX	INTEGER
			MAX-ACCESS	read-only
			STATUS	current
			::= { hmWanMbus46 34 }

hmWanMbus46Value0E		OBJECT-TYPE
			SYNTAX	INTEGER
			MAX-ACCESS	read-only
			STATUS	current
			::= { hmWanMbus46 35 }

hmWanMbus46VIF0F		OBJECT-TYPE
			SYNTAX	INTEGER
			MAX-ACCESS	read-only
			STATUS	current
			::= { hmWanMbus46 36 }

hmWanMbus46Value0F		OBJECT-TYPE
			SYNTAX	INTEGER
			MAX-ACCESS	read-only
			STATUS	current
			::= { hmWanMbus46 37 }

hmWanMbus46VIF10		OBJECT-TYPE
			SYNTAX	INTEGER
			MAX-ACCESS	read-only
			STATUS	current
			::= { hmWanMbus46 38 }

hmWanMbus46Value10		OBJECT-TYPE
			SYNTAX	INTEGER
			MAX-ACCESS	read-only
			STATUS	current
			::= { hmWanMbus46 39 }

hmWanMbus46VIF11		OBJECT-TYPE
			SYNTAX	INTEGER
			MAX-ACCESS	read-only
			STATUS	current
			::= { hmWanMbus46 40 }

hmWanMbus46Value11		OBJECT-TYPE
			SYNTAX	INTEGER
			MAX-ACCESS	read-only
			STATUS	current
			::= { hmWanMbus46 41 }

hmWanMbus46VIF12		OBJECT-TYPE
			SYNTAX	INTEGER
			MAX-ACCESS	read-only
			STATUS	current
			::= { hmWanMbus46 42 }

hmWanMbus46Value12		OBJECT-TYPE
			SYNTAX	INTEGER
			MAX-ACCESS	read-only
			STATUS	current
			::= { hmWanMbus46 43 }

hmWanMbus46VIF13		OBJECT-TYPE
			SYNTAX	INTEGER
			MAX-ACCESS	read-only
			STATUS	current
			::= { hmWanMbus46 44 }

hmWanMbus46Value13		OBJECT-TYPE
			SYNTAX	INTEGER
			MAX-ACCESS	read-only
			STATUS	current
			::= { hmWanMbus46 45 }

hmWanMbus46VIF14		OBJECT-TYPE
			SYNTAX	INTEGER
			MAX-ACCESS	read-only
			STATUS	current
			::= { hmWanMbus46 46 }

hmWanMbus46Value14		OBJECT-TYPE
			SYNTAX	INTEGER
			MAX-ACCESS	read-only
			STATUS	current
			::= { hmWanMbus46 47 }

hmWanMbus46VIF15		OBJECT-TYPE
			SYNTAX	INTEGER
			MAX-ACCESS	read-only
			STATUS	current
			::= { hmWanMbus46 48 }

hmWanMbus46Value15		OBJECT-TYPE
			SYNTAX	INTEGER
			MAX-ACCESS	read-only
			STATUS	current
			::= { hmWanMbus46 49 }

hmWanMbus46VIF16		OBJECT-TYPE
			SYNTAX	INTEGER
			MAX-ACCESS	read-only
			STATUS	current
			::= { hmWanMbus46 50 }

hmWanMbus46Value16		OBJECT-TYPE
			SYNTAX	INTEGER
			MAX-ACCESS	read-only
			STATUS	current
			::= { hmWanMbus46 51 }

hmWanMbus46VIF17		OBJECT-TYPE
			SYNTAX	INTEGER
			MAX-ACCESS	read-only
			STATUS	current
			::= { hmWanMbus46 52 }

hmWanMbus46Value17		OBJECT-TYPE
			SYNTAX	INTEGER
			MAX-ACCESS	read-only
			STATUS	current
			::= { hmWanMbus46 53 }

hmWanMbus46VIF18		OBJECT-TYPE
			SYNTAX	INTEGER
			MAX-ACCESS	read-only
			STATUS	current
			::= { hmWanMbus46 54 }

hmWanMbus46Value18		OBJECT-TYPE
			SYNTAX	INTEGER
			MAX-ACCESS	read-only
			STATUS	current
			::= { hmWanMbus46 55 }

hmWanMbus46VIF19		OBJECT-TYPE
			SYNTAX	INTEGER
			MAX-ACCESS	read-only
			STATUS	current
			::= { hmWanMbus46 56 }

hmWanMbus46Value19		OBJECT-TYPE
			SYNTAX	INTEGER
			MAX-ACCESS	read-only
			STATUS	current
			::= { hmWanMbus46 57 }

hmWanMbus46VIF1A		OBJECT-TYPE
			SYNTAX	INTEGER
			MAX-ACCESS	read-only
			STATUS	current
			::= { hmWanMbus46 58 }

hmWanMbus46Value1A		OBJECT-TYPE
			SYNTAX	INTEGER
			MAX-ACCESS	read-only
			STATUS	current
			::= { hmWanMbus46 59 }

hmWanMbus46VIF1B		OBJECT-TYPE
			SYNTAX	INTEGER
			MAX-ACCESS	read-only
			STATUS	current
			::= { hmWanMbus46 60 }

hmWanMbus46Value1B		OBJECT-TYPE
			SYNTAX	INTEGER
			MAX-ACCESS	read-only
			STATUS	current
			::= { hmWanMbus46 61 }

hmWanMbus46VIF1C		OBJECT-TYPE
			SYNTAX	INTEGER
			MAX-ACCESS	read-only
			STATUS	current
			::= { hmWanMbus46 62 }

hmWanMbus46Value1C		OBJECT-TYPE
			SYNTAX	INTEGER
			MAX-ACCESS	read-only
			STATUS	current
			::= { hmWanMbus46 63 }

hmWanMbus46VIF1D		OBJECT-TYPE
			SYNTAX	INTEGER
			MAX-ACCESS	read-only
			STATUS	current
			::= { hmWanMbus46 64 }

hmWanMbus46Value1D		OBJECT-TYPE
			SYNTAX	INTEGER
			MAX-ACCESS	read-only
			STATUS	current
			::= { hmWanMbus46 65 }

hmWanMbus46VIF1E		OBJECT-TYPE
			SYNTAX	INTEGER
			MAX-ACCESS	read-only
			STATUS	current
			::= { hmWanMbus46 66 }

hmWanMbus46Value1E		OBJECT-TYPE
			SYNTAX	INTEGER
			MAX-ACCESS	read-only
			STATUS	current
			::= { hmWanMbus46 67 }

hmWanMbus46VIF1F		OBJECT-TYPE
			SYNTAX	INTEGER
			MAX-ACCESS	read-only
			STATUS	current
			::= { hmWanMbus46 68 }

hmWanMbus46Value1F		OBJECT-TYPE
			SYNTAX	INTEGER
			MAX-ACCESS	read-only
			STATUS	current
			::= { hmWanMbus46 69 }

hmWanMbus46VIF20		OBJECT-TYPE
			SYNTAX	INTEGER
			MAX-ACCESS	read-only
			STATUS	current
			::= { hmWanMbus46 70 }

hmWanMbus46Value20		OBJECT-TYPE
			SYNTAX	INTEGER
			MAX-ACCESS	read-only
			STATUS	current
			::= { hmWanMbus46 71 }

hmWanMbus46VIF21		OBJECT-TYPE
			SYNTAX	INTEGER
			MAX-ACCESS	read-only
			STATUS	current
			::= { hmWanMbus46 72 }

hmWanMbus46Value21		OBJECT-TYPE
			SYNTAX	INTEGER
			MAX-ACCESS	read-only
			STATUS	current
			::= { hmWanMbus46 73 }

hmWanMbus46VIF22		OBJECT-TYPE
			SYNTAX	INTEGER
			MAX-ACCESS	read-only
			STATUS	current
			::= { hmWanMbus46 74 }

hmWanMbus46Value22		OBJECT-TYPE
			SYNTAX	INTEGER
			MAX-ACCESS	read-only
			STATUS	current
			::= { hmWanMbus46 75 }

hmWanMbus46VIF23		OBJECT-TYPE
			SYNTAX	INTEGER
			MAX-ACCESS	read-only
			STATUS	current
			::= { hmWanMbus46 76 }

hmWanMbus46Value23		OBJECT-TYPE
			SYNTAX	INTEGER
			MAX-ACCESS	read-only
			STATUS	current
			::= { hmWanMbus46 77 }

hmWanMbus46VIF24		OBJECT-TYPE
			SYNTAX	INTEGER
			MAX-ACCESS	read-only
			STATUS	current
			::= { hmWanMbus46 78 }

hmWanMbus46Value24		OBJECT-TYPE
			SYNTAX	INTEGER
			MAX-ACCESS	read-only
			STATUS	current
			::= { hmWanMbus46 79 }

hmWanMbus46VIF25		OBJECT-TYPE
			SYNTAX	INTEGER
			MAX-ACCESS	read-only
			STATUS	current
			::= { hmWanMbus46 80 }

hmWanMbus46Value25		OBJECT-TYPE
			SYNTAX	INTEGER
			MAX-ACCESS	read-only
			STATUS	current
			::= { hmWanMbus46 81 }

hmWanMbus46VIF26		OBJECT-TYPE
			SYNTAX	INTEGER
			MAX-ACCESS	read-only
			STATUS	current
			::= { hmWanMbus46 82 }

hmWanMbus46Value26		OBJECT-TYPE
			SYNTAX	INTEGER
			MAX-ACCESS	read-only
			STATUS	current
			::= { hmWanMbus46 83 }

hmWanMbus46VIF27		OBJECT-TYPE
			SYNTAX	INTEGER
			MAX-ACCESS	read-only
			STATUS	current
			::= { hmWanMbus46 84 }

hmWanMbus46Value27		OBJECT-TYPE
			SYNTAX	INTEGER
			MAX-ACCESS	read-only
			STATUS	current
			::= { hmWanMbus46 85 }

hmWanMbus46VIF28		OBJECT-TYPE
			SYNTAX	INTEGER
			MAX-ACCESS	read-only
			STATUS	current
			::= { hmWanMbus46 86 }

hmWanMbus46Value28		OBJECT-TYPE
			SYNTAX	INTEGER
			MAX-ACCESS	read-only
			STATUS	current
			::= { hmWanMbus46 87 }

hmWanMbus46VIF29		OBJECT-TYPE
			SYNTAX	INTEGER
			MAX-ACCESS	read-only
			STATUS	current
			::= { hmWanMbus46 88 }

hmWanMbus46Value29		OBJECT-TYPE
			SYNTAX	INTEGER
			MAX-ACCESS	read-only
			STATUS	current
			::= { hmWanMbus46 89 }

hmWanMbus46VIF2A		OBJECT-TYPE
			SYNTAX	INTEGER
			MAX-ACCESS	read-only
			STATUS	current
			::= { hmWanMbus46 90 }

hmWanMbus46Value2A		OBJECT-TYPE
			SYNTAX	INTEGER
			MAX-ACCESS	read-only
			STATUS	current
			::= { hmWanMbus46 91 }

hmWanMbus46VIF2B		OBJECT-TYPE
			SYNTAX	INTEGER
			MAX-ACCESS	read-only
			STATUS	current
			::= { hmWanMbus46 92 }

hmWanMbus46Value2B		OBJECT-TYPE
			SYNTAX	INTEGER
			MAX-ACCESS	read-only
			STATUS	current
			::= { hmWanMbus46 93 }

hmWanMbus46VIF2C		OBJECT-TYPE
			SYNTAX	INTEGER
			MAX-ACCESS	read-only
			STATUS	current
			::= { hmWanMbus46 94 }

hmWanMbus46Value2C		OBJECT-TYPE
			SYNTAX	INTEGER
			MAX-ACCESS	read-only
			STATUS	current
			::= { hmWanMbus46 95 }

hmWanMbus46VIF2D		OBJECT-TYPE
			SYNTAX	INTEGER
			MAX-ACCESS	read-only
			STATUS	current
			::= { hmWanMbus46 96 }

hmWanMbus46Value2D		OBJECT-TYPE
			SYNTAX	INTEGER
			MAX-ACCESS	read-only
			STATUS	current
			::= { hmWanMbus46 97 }

hmWanMbus46VIF2E		OBJECT-TYPE
			SYNTAX	INTEGER
			MAX-ACCESS	read-only
			STATUS	current
			::= { hmWanMbus46 98 }

hmWanMbus46Value2E		OBJECT-TYPE
			SYNTAX	INTEGER
			MAX-ACCESS	read-only
			STATUS	current
			::= { hmWanMbus46 99 }

hmWanMbus46VIF2F		OBJECT-TYPE
			SYNTAX	INTEGER
			MAX-ACCESS	read-only
			STATUS	current
			::= { hmWanMbus46 100 }

hmWanMbus46Value2F		OBJECT-TYPE
			SYNTAX	INTEGER
			MAX-ACCESS	read-only
			STATUS	current
			::= { hmWanMbus46 101 }

hmWanMbus47			OBJECT IDENTIFIER ::= { hmWanMbus 71 }

hmWanMbus47IdNumber		OBJECT-TYPE
			SYNTAX	Gauge32
			MAX-ACCESS	read-only
			STATUS	current
			::= { hmWanMbus47 1 }

hmWanMbus47Manufacturer	OBJECT-TYPE
			SYNTAX	Gauge32
			MAX-ACCESS	read-only
			STATUS	current
			::= { hmWanMbus47 2 }

hmWanMbus47Version		OBJECT-TYPE
			SYNTAX	Gauge32
			MAX-ACCESS	read-only
			STATUS	current
			::= { hmWanMbus47 3 }

hmWanMbus47Medium		OBJECT-TYPE
			SYNTAX	Gauge32
			MAX-ACCESS	read-only
			STATUS	current
			::= { hmWanMbus47 4 }

hmWanMbus47Status		OBJECT-TYPE
			SYNTAX	Gauge32
			MAX-ACCESS	read-only
			STATUS	current
			::= { hmWanMbus47 5 }

hmWanMbus47VIF00		OBJECT-TYPE
			SYNTAX	INTEGER
			MAX-ACCESS	read-only
			STATUS	current
			::= { hmWanMbus47 6 }

hmWanMbus47Value00		OBJECT-TYPE
			SYNTAX	INTEGER
			MAX-ACCESS	read-only
			STATUS	current
			::= { hmWanMbus47 7 }

hmWanMbus47VIF01		OBJECT-TYPE
			SYNTAX	INTEGER
			MAX-ACCESS	read-only
			STATUS	current
			::= { hmWanMbus47 8 }

hmWanMbus47Value01		OBJECT-TYPE
			SYNTAX	INTEGER
			MAX-ACCESS	read-only
			STATUS	current
			::= { hmWanMbus47 9 }

hmWanMbus47VIF02		OBJECT-TYPE
			SYNTAX	INTEGER
			MAX-ACCESS	read-only
			STATUS	current
			::= { hmWanMbus47 10 }

hmWanMbus47Value02		OBJECT-TYPE
			SYNTAX	INTEGER
			MAX-ACCESS	read-only
			STATUS	current
			::= { hmWanMbus47 11 }

hmWanMbus47VIF03		OBJECT-TYPE
			SYNTAX	INTEGER
			MAX-ACCESS	read-only
			STATUS	current
			::= { hmWanMbus47 12 }

hmWanMbus47Value03		OBJECT-TYPE
			SYNTAX	INTEGER
			MAX-ACCESS	read-only
			STATUS	current
			::= { hmWanMbus47 13 }

hmWanMbus47VIF04		OBJECT-TYPE
			SYNTAX	INTEGER
			MAX-ACCESS	read-only
			STATUS	current
			::= { hmWanMbus47 14 }

hmWanMbus47Value04		OBJECT-TYPE
			SYNTAX	INTEGER
			MAX-ACCESS	read-only
			STATUS	current
			::= { hmWanMbus47 15 }

hmWanMbus47VIF05		OBJECT-TYPE
			SYNTAX	INTEGER
			MAX-ACCESS	read-only
			STATUS	current
			::= { hmWanMbus47 16 }

hmWanMbus47Value05		OBJECT-TYPE
			SYNTAX	INTEGER
			MAX-ACCESS	read-only
			STATUS	current
			::= { hmWanMbus47 17 }

hmWanMbus47VIF06		OBJECT-TYPE
			SYNTAX	INTEGER
			MAX-ACCESS	read-only
			STATUS	current
			::= { hmWanMbus47 18 }

hmWanMbus47Value06		OBJECT-TYPE
			SYNTAX	INTEGER
			MAX-ACCESS	read-only
			STATUS	current
			::= { hmWanMbus47 19 }

hmWanMbus47VIF07		OBJECT-TYPE
			SYNTAX	INTEGER
			MAX-ACCESS	read-only
			STATUS	current
			::= { hmWanMbus47 20 }

hmWanMbus47Value07		OBJECT-TYPE
			SYNTAX	INTEGER
			MAX-ACCESS	read-only
			STATUS	current
			::= { hmWanMbus47 21 }

hmWanMbus47VIF08		OBJECT-TYPE
			SYNTAX	INTEGER
			MAX-ACCESS	read-only
			STATUS	current
			::= { hmWanMbus47 22 }

hmWanMbus47Value08		OBJECT-TYPE
			SYNTAX	INTEGER
			MAX-ACCESS	read-only
			STATUS	current
			::= { hmWanMbus47 23 }

hmWanMbus47VIF09		OBJECT-TYPE
			SYNTAX	INTEGER
			MAX-ACCESS	read-only
			STATUS	current
			::= { hmWanMbus47 24 }

hmWanMbus47Value09		OBJECT-TYPE
			SYNTAX	INTEGER
			MAX-ACCESS	read-only
			STATUS	current
			::= { hmWanMbus47 25 }

hmWanMbus47VIF0A		OBJECT-TYPE
			SYNTAX	INTEGER
			MAX-ACCESS	read-only
			STATUS	current
			::= { hmWanMbus47 26 }

hmWanMbus47Value0A		OBJECT-TYPE
			SYNTAX	INTEGER
			MAX-ACCESS	read-only
			STATUS	current
			::= { hmWanMbus47 27 }

hmWanMbus47VIF0B		OBJECT-TYPE
			SYNTAX	INTEGER
			MAX-ACCESS	read-only
			STATUS	current
			::= { hmWanMbus47 28 }

hmWanMbus47Value0B		OBJECT-TYPE
			SYNTAX	INTEGER
			MAX-ACCESS	read-only
			STATUS	current
			::= { hmWanMbus47 29 }

hmWanMbus47VIF0C		OBJECT-TYPE
			SYNTAX	INTEGER
			MAX-ACCESS	read-only
			STATUS	current
			::= { hmWanMbus47 30 }

hmWanMbus47Value0C		OBJECT-TYPE
			SYNTAX	INTEGER
			MAX-ACCESS	read-only
			STATUS	current
			::= { hmWanMbus47 31 }

hmWanMbus47VIF0D		OBJECT-TYPE
			SYNTAX	INTEGER
			MAX-ACCESS	read-only
			STATUS	current
			::= { hmWanMbus47 32 }

hmWanMbus47Value0D		OBJECT-TYPE
			SYNTAX	INTEGER
			MAX-ACCESS	read-only
			STATUS	current
			::= { hmWanMbus47 33 }

hmWanMbus47VIF0E		OBJECT-TYPE
			SYNTAX	INTEGER
			MAX-ACCESS	read-only
			STATUS	current
			::= { hmWanMbus47 34 }

hmWanMbus47Value0E		OBJECT-TYPE
			SYNTAX	INTEGER
			MAX-ACCESS	read-only
			STATUS	current
			::= { hmWanMbus47 35 }

hmWanMbus47VIF0F		OBJECT-TYPE
			SYNTAX	INTEGER
			MAX-ACCESS	read-only
			STATUS	current
			::= { hmWanMbus47 36 }

hmWanMbus47Value0F		OBJECT-TYPE
			SYNTAX	INTEGER
			MAX-ACCESS	read-only
			STATUS	current
			::= { hmWanMbus47 37 }

hmWanMbus47VIF10		OBJECT-TYPE
			SYNTAX	INTEGER
			MAX-ACCESS	read-only
			STATUS	current
			::= { hmWanMbus47 38 }

hmWanMbus47Value10		OBJECT-TYPE
			SYNTAX	INTEGER
			MAX-ACCESS	read-only
			STATUS	current
			::= { hmWanMbus47 39 }

hmWanMbus47VIF11		OBJECT-TYPE
			SYNTAX	INTEGER
			MAX-ACCESS	read-only
			STATUS	current
			::= { hmWanMbus47 40 }

hmWanMbus47Value11		OBJECT-TYPE
			SYNTAX	INTEGER
			MAX-ACCESS	read-only
			STATUS	current
			::= { hmWanMbus47 41 }

hmWanMbus47VIF12		OBJECT-TYPE
			SYNTAX	INTEGER
			MAX-ACCESS	read-only
			STATUS	current
			::= { hmWanMbus47 42 }

hmWanMbus47Value12		OBJECT-TYPE
			SYNTAX	INTEGER
			MAX-ACCESS	read-only
			STATUS	current
			::= { hmWanMbus47 43 }

hmWanMbus47VIF13		OBJECT-TYPE
			SYNTAX	INTEGER
			MAX-ACCESS	read-only
			STATUS	current
			::= { hmWanMbus47 44 }

hmWanMbus47Value13		OBJECT-TYPE
			SYNTAX	INTEGER
			MAX-ACCESS	read-only
			STATUS	current
			::= { hmWanMbus47 45 }

hmWanMbus47VIF14		OBJECT-TYPE
			SYNTAX	INTEGER
			MAX-ACCESS	read-only
			STATUS	current
			::= { hmWanMbus47 46 }

hmWanMbus47Value14		OBJECT-TYPE
			SYNTAX	INTEGER
			MAX-ACCESS	read-only
			STATUS	current
			::= { hmWanMbus47 47 }

hmWanMbus47VIF15		OBJECT-TYPE
			SYNTAX	INTEGER
			MAX-ACCESS	read-only
			STATUS	current
			::= { hmWanMbus47 48 }

hmWanMbus47Value15		OBJECT-TYPE
			SYNTAX	INTEGER
			MAX-ACCESS	read-only
			STATUS	current
			::= { hmWanMbus47 49 }

hmWanMbus47VIF16		OBJECT-TYPE
			SYNTAX	INTEGER
			MAX-ACCESS	read-only
			STATUS	current
			::= { hmWanMbus47 50 }

hmWanMbus47Value16		OBJECT-TYPE
			SYNTAX	INTEGER
			MAX-ACCESS	read-only
			STATUS	current
			::= { hmWanMbus47 51 }

hmWanMbus47VIF17		OBJECT-TYPE
			SYNTAX	INTEGER
			MAX-ACCESS	read-only
			STATUS	current
			::= { hmWanMbus47 52 }

hmWanMbus47Value17		OBJECT-TYPE
			SYNTAX	INTEGER
			MAX-ACCESS	read-only
			STATUS	current
			::= { hmWanMbus47 53 }

hmWanMbus47VIF18		OBJECT-TYPE
			SYNTAX	INTEGER
			MAX-ACCESS	read-only
			STATUS	current
			::= { hmWanMbus47 54 }

hmWanMbus47Value18		OBJECT-TYPE
			SYNTAX	INTEGER
			MAX-ACCESS	read-only
			STATUS	current
			::= { hmWanMbus47 55 }

hmWanMbus47VIF19		OBJECT-TYPE
			SYNTAX	INTEGER
			MAX-ACCESS	read-only
			STATUS	current
			::= { hmWanMbus47 56 }

hmWanMbus47Value19		OBJECT-TYPE
			SYNTAX	INTEGER
			MAX-ACCESS	read-only
			STATUS	current
			::= { hmWanMbus47 57 }

hmWanMbus47VIF1A		OBJECT-TYPE
			SYNTAX	INTEGER
			MAX-ACCESS	read-only
			STATUS	current
			::= { hmWanMbus47 58 }

hmWanMbus47Value1A		OBJECT-TYPE
			SYNTAX	INTEGER
			MAX-ACCESS	read-only
			STATUS	current
			::= { hmWanMbus47 59 }

hmWanMbus47VIF1B		OBJECT-TYPE
			SYNTAX	INTEGER
			MAX-ACCESS	read-only
			STATUS	current
			::= { hmWanMbus47 60 }

hmWanMbus47Value1B		OBJECT-TYPE
			SYNTAX	INTEGER
			MAX-ACCESS	read-only
			STATUS	current
			::= { hmWanMbus47 61 }

hmWanMbus47VIF1C		OBJECT-TYPE
			SYNTAX	INTEGER
			MAX-ACCESS	read-only
			STATUS	current
			::= { hmWanMbus47 62 }

hmWanMbus47Value1C		OBJECT-TYPE
			SYNTAX	INTEGER
			MAX-ACCESS	read-only
			STATUS	current
			::= { hmWanMbus47 63 }

hmWanMbus47VIF1D		OBJECT-TYPE
			SYNTAX	INTEGER
			MAX-ACCESS	read-only
			STATUS	current
			::= { hmWanMbus47 64 }

hmWanMbus47Value1D		OBJECT-TYPE
			SYNTAX	INTEGER
			MAX-ACCESS	read-only
			STATUS	current
			::= { hmWanMbus47 65 }

hmWanMbus47VIF1E		OBJECT-TYPE
			SYNTAX	INTEGER
			MAX-ACCESS	read-only
			STATUS	current
			::= { hmWanMbus47 66 }

hmWanMbus47Value1E		OBJECT-TYPE
			SYNTAX	INTEGER
			MAX-ACCESS	read-only
			STATUS	current
			::= { hmWanMbus47 67 }

hmWanMbus47VIF1F		OBJECT-TYPE
			SYNTAX	INTEGER
			MAX-ACCESS	read-only
			STATUS	current
			::= { hmWanMbus47 68 }

hmWanMbus47Value1F		OBJECT-TYPE
			SYNTAX	INTEGER
			MAX-ACCESS	read-only
			STATUS	current
			::= { hmWanMbus47 69 }

hmWanMbus47VIF20		OBJECT-TYPE
			SYNTAX	INTEGER
			MAX-ACCESS	read-only
			STATUS	current
			::= { hmWanMbus47 70 }

hmWanMbus47Value20		OBJECT-TYPE
			SYNTAX	INTEGER
			MAX-ACCESS	read-only
			STATUS	current
			::= { hmWanMbus47 71 }

hmWanMbus47VIF21		OBJECT-TYPE
			SYNTAX	INTEGER
			MAX-ACCESS	read-only
			STATUS	current
			::= { hmWanMbus47 72 }

hmWanMbus47Value21		OBJECT-TYPE
			SYNTAX	INTEGER
			MAX-ACCESS	read-only
			STATUS	current
			::= { hmWanMbus47 73 }

hmWanMbus47VIF22		OBJECT-TYPE
			SYNTAX	INTEGER
			MAX-ACCESS	read-only
			STATUS	current
			::= { hmWanMbus47 74 }

hmWanMbus47Value22		OBJECT-TYPE
			SYNTAX	INTEGER
			MAX-ACCESS	read-only
			STATUS	current
			::= { hmWanMbus47 75 }

hmWanMbus47VIF23		OBJECT-TYPE
			SYNTAX	INTEGER
			MAX-ACCESS	read-only
			STATUS	current
			::= { hmWanMbus47 76 }

hmWanMbus47Value23		OBJECT-TYPE
			SYNTAX	INTEGER
			MAX-ACCESS	read-only
			STATUS	current
			::= { hmWanMbus47 77 }

hmWanMbus47VIF24		OBJECT-TYPE
			SYNTAX	INTEGER
			MAX-ACCESS	read-only
			STATUS	current
			::= { hmWanMbus47 78 }

hmWanMbus47Value24		OBJECT-TYPE
			SYNTAX	INTEGER
			MAX-ACCESS	read-only
			STATUS	current
			::= { hmWanMbus47 79 }

hmWanMbus47VIF25		OBJECT-TYPE
			SYNTAX	INTEGER
			MAX-ACCESS	read-only
			STATUS	current
			::= { hmWanMbus47 80 }

hmWanMbus47Value25		OBJECT-TYPE
			SYNTAX	INTEGER
			MAX-ACCESS	read-only
			STATUS	current
			::= { hmWanMbus47 81 }

hmWanMbus47VIF26		OBJECT-TYPE
			SYNTAX	INTEGER
			MAX-ACCESS	read-only
			STATUS	current
			::= { hmWanMbus47 82 }

hmWanMbus47Value26		OBJECT-TYPE
			SYNTAX	INTEGER
			MAX-ACCESS	read-only
			STATUS	current
			::= { hmWanMbus47 83 }

hmWanMbus47VIF27		OBJECT-TYPE
			SYNTAX	INTEGER
			MAX-ACCESS	read-only
			STATUS	current
			::= { hmWanMbus47 84 }

hmWanMbus47Value27		OBJECT-TYPE
			SYNTAX	INTEGER
			MAX-ACCESS	read-only
			STATUS	current
			::= { hmWanMbus47 85 }

hmWanMbus47VIF28		OBJECT-TYPE
			SYNTAX	INTEGER
			MAX-ACCESS	read-only
			STATUS	current
			::= { hmWanMbus47 86 }

hmWanMbus47Value28		OBJECT-TYPE
			SYNTAX	INTEGER
			MAX-ACCESS	read-only
			STATUS	current
			::= { hmWanMbus47 87 }

hmWanMbus47VIF29		OBJECT-TYPE
			SYNTAX	INTEGER
			MAX-ACCESS	read-only
			STATUS	current
			::= { hmWanMbus47 88 }

hmWanMbus47Value29		OBJECT-TYPE
			SYNTAX	INTEGER
			MAX-ACCESS	read-only
			STATUS	current
			::= { hmWanMbus47 89 }

hmWanMbus47VIF2A		OBJECT-TYPE
			SYNTAX	INTEGER
			MAX-ACCESS	read-only
			STATUS	current
			::= { hmWanMbus47 90 }

hmWanMbus47Value2A		OBJECT-TYPE
			SYNTAX	INTEGER
			MAX-ACCESS	read-only
			STATUS	current
			::= { hmWanMbus47 91 }

hmWanMbus47VIF2B		OBJECT-TYPE
			SYNTAX	INTEGER
			MAX-ACCESS	read-only
			STATUS	current
			::= { hmWanMbus47 92 }

hmWanMbus47Value2B		OBJECT-TYPE
			SYNTAX	INTEGER
			MAX-ACCESS	read-only
			STATUS	current
			::= { hmWanMbus47 93 }

hmWanMbus47VIF2C		OBJECT-TYPE
			SYNTAX	INTEGER
			MAX-ACCESS	read-only
			STATUS	current
			::= { hmWanMbus47 94 }

hmWanMbus47Value2C		OBJECT-TYPE
			SYNTAX	INTEGER
			MAX-ACCESS	read-only
			STATUS	current
			::= { hmWanMbus47 95 }

hmWanMbus47VIF2D		OBJECT-TYPE
			SYNTAX	INTEGER
			MAX-ACCESS	read-only
			STATUS	current
			::= { hmWanMbus47 96 }

hmWanMbus47Value2D		OBJECT-TYPE
			SYNTAX	INTEGER
			MAX-ACCESS	read-only
			STATUS	current
			::= { hmWanMbus47 97 }

hmWanMbus47VIF2E		OBJECT-TYPE
			SYNTAX	INTEGER
			MAX-ACCESS	read-only
			STATUS	current
			::= { hmWanMbus47 98 }

hmWanMbus47Value2E		OBJECT-TYPE
			SYNTAX	INTEGER
			MAX-ACCESS	read-only
			STATUS	current
			::= { hmWanMbus47 99 }

hmWanMbus47VIF2F		OBJECT-TYPE
			SYNTAX	INTEGER
			MAX-ACCESS	read-only
			STATUS	current
			::= { hmWanMbus47 100 }

hmWanMbus47Value2F		OBJECT-TYPE
			SYNTAX	INTEGER
			MAX-ACCESS	read-only
			STATUS	current
			::= { hmWanMbus47 101 }

hmWanMbus48			OBJECT IDENTIFIER ::= { hmWanMbus 72 }

hmWanMbus48IdNumber		OBJECT-TYPE
			SYNTAX	Gauge32
			MAX-ACCESS	read-only
			STATUS	current
			::= { hmWanMbus48 1 }

hmWanMbus48Manufacturer	OBJECT-TYPE
			SYNTAX	Gauge32
			MAX-ACCESS	read-only
			STATUS	current
			::= { hmWanMbus48 2 }

hmWanMbus48Version		OBJECT-TYPE
			SYNTAX	Gauge32
			MAX-ACCESS	read-only
			STATUS	current
			::= { hmWanMbus48 3 }

hmWanMbus48Medium		OBJECT-TYPE
			SYNTAX	Gauge32
			MAX-ACCESS	read-only
			STATUS	current
			::= { hmWanMbus48 4 }

hmWanMbus48Status		OBJECT-TYPE
			SYNTAX	Gauge32
			MAX-ACCESS	read-only
			STATUS	current
			::= { hmWanMbus48 5 }

hmWanMbus48VIF00		OBJECT-TYPE
			SYNTAX	INTEGER
			MAX-ACCESS	read-only
			STATUS	current
			::= { hmWanMbus48 6 }

hmWanMbus48Value00		OBJECT-TYPE
			SYNTAX	INTEGER
			MAX-ACCESS	read-only
			STATUS	current
			::= { hmWanMbus48 7 }

hmWanMbus48VIF01		OBJECT-TYPE
			SYNTAX	INTEGER
			MAX-ACCESS	read-only
			STATUS	current
			::= { hmWanMbus48 8 }

hmWanMbus48Value01		OBJECT-TYPE
			SYNTAX	INTEGER
			MAX-ACCESS	read-only
			STATUS	current
			::= { hmWanMbus48 9 }

hmWanMbus48VIF02		OBJECT-TYPE
			SYNTAX	INTEGER
			MAX-ACCESS	read-only
			STATUS	current
			::= { hmWanMbus48 10 }

hmWanMbus48Value02		OBJECT-TYPE
			SYNTAX	INTEGER
			MAX-ACCESS	read-only
			STATUS	current
			::= { hmWanMbus48 11 }

hmWanMbus48VIF03		OBJECT-TYPE
			SYNTAX	INTEGER
			MAX-ACCESS	read-only
			STATUS	current
			::= { hmWanMbus48 12 }

hmWanMbus48Value03		OBJECT-TYPE
			SYNTAX	INTEGER
			MAX-ACCESS	read-only
			STATUS	current
			::= { hmWanMbus48 13 }

hmWanMbus48VIF04		OBJECT-TYPE
			SYNTAX	INTEGER
			MAX-ACCESS	read-only
			STATUS	current
			::= { hmWanMbus48 14 }

hmWanMbus48Value04		OBJECT-TYPE
			SYNTAX	INTEGER
			MAX-ACCESS	read-only
			STATUS	current
			::= { hmWanMbus48 15 }

hmWanMbus48VIF05		OBJECT-TYPE
			SYNTAX	INTEGER
			MAX-ACCESS	read-only
			STATUS	current
			::= { hmWanMbus48 16 }

hmWanMbus48Value05		OBJECT-TYPE
			SYNTAX	INTEGER
			MAX-ACCESS	read-only
			STATUS	current
			::= { hmWanMbus48 17 }

hmWanMbus48VIF06		OBJECT-TYPE
			SYNTAX	INTEGER
			MAX-ACCESS	read-only
			STATUS	current
			::= { hmWanMbus48 18 }

hmWanMbus48Value06		OBJECT-TYPE
			SYNTAX	INTEGER
			MAX-ACCESS	read-only
			STATUS	current
			::= { hmWanMbus48 19 }

hmWanMbus48VIF07		OBJECT-TYPE
			SYNTAX	INTEGER
			MAX-ACCESS	read-only
			STATUS	current
			::= { hmWanMbus48 20 }

hmWanMbus48Value07		OBJECT-TYPE
			SYNTAX	INTEGER
			MAX-ACCESS	read-only
			STATUS	current
			::= { hmWanMbus48 21 }

hmWanMbus48VIF08		OBJECT-TYPE
			SYNTAX	INTEGER
			MAX-ACCESS	read-only
			STATUS	current
			::= { hmWanMbus48 22 }

hmWanMbus48Value08		OBJECT-TYPE
			SYNTAX	INTEGER
			MAX-ACCESS	read-only
			STATUS	current
			::= { hmWanMbus48 23 }

hmWanMbus48VIF09		OBJECT-TYPE
			SYNTAX	INTEGER
			MAX-ACCESS	read-only
			STATUS	current
			::= { hmWanMbus48 24 }

hmWanMbus48Value09		OBJECT-TYPE
			SYNTAX	INTEGER
			MAX-ACCESS	read-only
			STATUS	current
			::= { hmWanMbus48 25 }

hmWanMbus48VIF0A		OBJECT-TYPE
			SYNTAX	INTEGER
			MAX-ACCESS	read-only
			STATUS	current
			::= { hmWanMbus48 26 }

hmWanMbus48Value0A		OBJECT-TYPE
			SYNTAX	INTEGER
			MAX-ACCESS	read-only
			STATUS	current
			::= { hmWanMbus48 27 }

hmWanMbus48VIF0B		OBJECT-TYPE
			SYNTAX	INTEGER
			MAX-ACCESS	read-only
			STATUS	current
			::= { hmWanMbus48 28 }

hmWanMbus48Value0B		OBJECT-TYPE
			SYNTAX	INTEGER
			MAX-ACCESS	read-only
			STATUS	current
			::= { hmWanMbus48 29 }

hmWanMbus48VIF0C		OBJECT-TYPE
			SYNTAX	INTEGER
			MAX-ACCESS	read-only
			STATUS	current
			::= { hmWanMbus48 30 }

hmWanMbus48Value0C		OBJECT-TYPE
			SYNTAX	INTEGER
			MAX-ACCESS	read-only
			STATUS	current
			::= { hmWanMbus48 31 }

hmWanMbus48VIF0D		OBJECT-TYPE
			SYNTAX	INTEGER
			MAX-ACCESS	read-only
			STATUS	current
			::= { hmWanMbus48 32 }

hmWanMbus48Value0D		OBJECT-TYPE
			SYNTAX	INTEGER
			MAX-ACCESS	read-only
			STATUS	current
			::= { hmWanMbus48 33 }

hmWanMbus48VIF0E		OBJECT-TYPE
			SYNTAX	INTEGER
			MAX-ACCESS	read-only
			STATUS	current
			::= { hmWanMbus48 34 }

hmWanMbus48Value0E		OBJECT-TYPE
			SYNTAX	INTEGER
			MAX-ACCESS	read-only
			STATUS	current
			::= { hmWanMbus48 35 }

hmWanMbus48VIF0F		OBJECT-TYPE
			SYNTAX	INTEGER
			MAX-ACCESS	read-only
			STATUS	current
			::= { hmWanMbus48 36 }

hmWanMbus48Value0F		OBJECT-TYPE
			SYNTAX	INTEGER
			MAX-ACCESS	read-only
			STATUS	current
			::= { hmWanMbus48 37 }

hmWanMbus48VIF10		OBJECT-TYPE
			SYNTAX	INTEGER
			MAX-ACCESS	read-only
			STATUS	current
			::= { hmWanMbus48 38 }

hmWanMbus48Value10		OBJECT-TYPE
			SYNTAX	INTEGER
			MAX-ACCESS	read-only
			STATUS	current
			::= { hmWanMbus48 39 }

hmWanMbus48VIF11		OBJECT-TYPE
			SYNTAX	INTEGER
			MAX-ACCESS	read-only
			STATUS	current
			::= { hmWanMbus48 40 }

hmWanMbus48Value11		OBJECT-TYPE
			SYNTAX	INTEGER
			MAX-ACCESS	read-only
			STATUS	current
			::= { hmWanMbus48 41 }

hmWanMbus48VIF12		OBJECT-TYPE
			SYNTAX	INTEGER
			MAX-ACCESS	read-only
			STATUS	current
			::= { hmWanMbus48 42 }

hmWanMbus48Value12		OBJECT-TYPE
			SYNTAX	INTEGER
			MAX-ACCESS	read-only
			STATUS	current
			::= { hmWanMbus48 43 }

hmWanMbus48VIF13		OBJECT-TYPE
			SYNTAX	INTEGER
			MAX-ACCESS	read-only
			STATUS	current
			::= { hmWanMbus48 44 }

hmWanMbus48Value13		OBJECT-TYPE
			SYNTAX	INTEGER
			MAX-ACCESS	read-only
			STATUS	current
			::= { hmWanMbus48 45 }

hmWanMbus48VIF14		OBJECT-TYPE
			SYNTAX	INTEGER
			MAX-ACCESS	read-only
			STATUS	current
			::= { hmWanMbus48 46 }

hmWanMbus48Value14		OBJECT-TYPE
			SYNTAX	INTEGER
			MAX-ACCESS	read-only
			STATUS	current
			::= { hmWanMbus48 47 }

hmWanMbus48VIF15		OBJECT-TYPE
			SYNTAX	INTEGER
			MAX-ACCESS	read-only
			STATUS	current
			::= { hmWanMbus48 48 }

hmWanMbus48Value15		OBJECT-TYPE
			SYNTAX	INTEGER
			MAX-ACCESS	read-only
			STATUS	current
			::= { hmWanMbus48 49 }

hmWanMbus48VIF16		OBJECT-TYPE
			SYNTAX	INTEGER
			MAX-ACCESS	read-only
			STATUS	current
			::= { hmWanMbus48 50 }

hmWanMbus48Value16		OBJECT-TYPE
			SYNTAX	INTEGER
			MAX-ACCESS	read-only
			STATUS	current
			::= { hmWanMbus48 51 }

hmWanMbus48VIF17		OBJECT-TYPE
			SYNTAX	INTEGER
			MAX-ACCESS	read-only
			STATUS	current
			::= { hmWanMbus48 52 }

hmWanMbus48Value17		OBJECT-TYPE
			SYNTAX	INTEGER
			MAX-ACCESS	read-only
			STATUS	current
			::= { hmWanMbus48 53 }

hmWanMbus48VIF18		OBJECT-TYPE
			SYNTAX	INTEGER
			MAX-ACCESS	read-only
			STATUS	current
			::= { hmWanMbus48 54 }

hmWanMbus48Value18		OBJECT-TYPE
			SYNTAX	INTEGER
			MAX-ACCESS	read-only
			STATUS	current
			::= { hmWanMbus48 55 }

hmWanMbus48VIF19		OBJECT-TYPE
			SYNTAX	INTEGER
			MAX-ACCESS	read-only
			STATUS	current
			::= { hmWanMbus48 56 }

hmWanMbus48Value19		OBJECT-TYPE
			SYNTAX	INTEGER
			MAX-ACCESS	read-only
			STATUS	current
			::= { hmWanMbus48 57 }

hmWanMbus48VIF1A		OBJECT-TYPE
			SYNTAX	INTEGER
			MAX-ACCESS	read-only
			STATUS	current
			::= { hmWanMbus48 58 }

hmWanMbus48Value1A		OBJECT-TYPE
			SYNTAX	INTEGER
			MAX-ACCESS	read-only
			STATUS	current
			::= { hmWanMbus48 59 }

hmWanMbus48VIF1B		OBJECT-TYPE
			SYNTAX	INTEGER
			MAX-ACCESS	read-only
			STATUS	current
			::= { hmWanMbus48 60 }

hmWanMbus48Value1B		OBJECT-TYPE
			SYNTAX	INTEGER
			MAX-ACCESS	read-only
			STATUS	current
			::= { hmWanMbus48 61 }

hmWanMbus48VIF1C		OBJECT-TYPE
			SYNTAX	INTEGER
			MAX-ACCESS	read-only
			STATUS	current
			::= { hmWanMbus48 62 }

hmWanMbus48Value1C		OBJECT-TYPE
			SYNTAX	INTEGER
			MAX-ACCESS	read-only
			STATUS	current
			::= { hmWanMbus48 63 }

hmWanMbus48VIF1D		OBJECT-TYPE
			SYNTAX	INTEGER
			MAX-ACCESS	read-only
			STATUS	current
			::= { hmWanMbus48 64 }

hmWanMbus48Value1D		OBJECT-TYPE
			SYNTAX	INTEGER
			MAX-ACCESS	read-only
			STATUS	current
			::= { hmWanMbus48 65 }

hmWanMbus48VIF1E		OBJECT-TYPE
			SYNTAX	INTEGER
			MAX-ACCESS	read-only
			STATUS	current
			::= { hmWanMbus48 66 }

hmWanMbus48Value1E		OBJECT-TYPE
			SYNTAX	INTEGER
			MAX-ACCESS	read-only
			STATUS	current
			::= { hmWanMbus48 67 }

hmWanMbus48VIF1F		OBJECT-TYPE
			SYNTAX	INTEGER
			MAX-ACCESS	read-only
			STATUS	current
			::= { hmWanMbus48 68 }

hmWanMbus48Value1F		OBJECT-TYPE
			SYNTAX	INTEGER
			MAX-ACCESS	read-only
			STATUS	current
			::= { hmWanMbus48 69 }

hmWanMbus48VIF20		OBJECT-TYPE
			SYNTAX	INTEGER
			MAX-ACCESS	read-only
			STATUS	current
			::= { hmWanMbus48 70 }

hmWanMbus48Value20		OBJECT-TYPE
			SYNTAX	INTEGER
			MAX-ACCESS	read-only
			STATUS	current
			::= { hmWanMbus48 71 }

hmWanMbus48VIF21		OBJECT-TYPE
			SYNTAX	INTEGER
			MAX-ACCESS	read-only
			STATUS	current
			::= { hmWanMbus48 72 }

hmWanMbus48Value21		OBJECT-TYPE
			SYNTAX	INTEGER
			MAX-ACCESS	read-only
			STATUS	current
			::= { hmWanMbus48 73 }

hmWanMbus48VIF22		OBJECT-TYPE
			SYNTAX	INTEGER
			MAX-ACCESS	read-only
			STATUS	current
			::= { hmWanMbus48 74 }

hmWanMbus48Value22		OBJECT-TYPE
			SYNTAX	INTEGER
			MAX-ACCESS	read-only
			STATUS	current
			::= { hmWanMbus48 75 }

hmWanMbus48VIF23		OBJECT-TYPE
			SYNTAX	INTEGER
			MAX-ACCESS	read-only
			STATUS	current
			::= { hmWanMbus48 76 }

hmWanMbus48Value23		OBJECT-TYPE
			SYNTAX	INTEGER
			MAX-ACCESS	read-only
			STATUS	current
			::= { hmWanMbus48 77 }

hmWanMbus48VIF24		OBJECT-TYPE
			SYNTAX	INTEGER
			MAX-ACCESS	read-only
			STATUS	current
			::= { hmWanMbus48 78 }

hmWanMbus48Value24		OBJECT-TYPE
			SYNTAX	INTEGER
			MAX-ACCESS	read-only
			STATUS	current
			::= { hmWanMbus48 79 }

hmWanMbus48VIF25		OBJECT-TYPE
			SYNTAX	INTEGER
			MAX-ACCESS	read-only
			STATUS	current
			::= { hmWanMbus48 80 }

hmWanMbus48Value25		OBJECT-TYPE
			SYNTAX	INTEGER
			MAX-ACCESS	read-only
			STATUS	current
			::= { hmWanMbus48 81 }

hmWanMbus48VIF26		OBJECT-TYPE
			SYNTAX	INTEGER
			MAX-ACCESS	read-only
			STATUS	current
			::= { hmWanMbus48 82 }

hmWanMbus48Value26		OBJECT-TYPE
			SYNTAX	INTEGER
			MAX-ACCESS	read-only
			STATUS	current
			::= { hmWanMbus48 83 }

hmWanMbus48VIF27		OBJECT-TYPE
			SYNTAX	INTEGER
			MAX-ACCESS	read-only
			STATUS	current
			::= { hmWanMbus48 84 }

hmWanMbus48Value27		OBJECT-TYPE
			SYNTAX	INTEGER
			MAX-ACCESS	read-only
			STATUS	current
			::= { hmWanMbus48 85 }

hmWanMbus48VIF28		OBJECT-TYPE
			SYNTAX	INTEGER
			MAX-ACCESS	read-only
			STATUS	current
			::= { hmWanMbus48 86 }

hmWanMbus48Value28		OBJECT-TYPE
			SYNTAX	INTEGER
			MAX-ACCESS	read-only
			STATUS	current
			::= { hmWanMbus48 87 }

hmWanMbus48VIF29		OBJECT-TYPE
			SYNTAX	INTEGER
			MAX-ACCESS	read-only
			STATUS	current
			::= { hmWanMbus48 88 }

hmWanMbus48Value29		OBJECT-TYPE
			SYNTAX	INTEGER
			MAX-ACCESS	read-only
			STATUS	current
			::= { hmWanMbus48 89 }

hmWanMbus48VIF2A		OBJECT-TYPE
			SYNTAX	INTEGER
			MAX-ACCESS	read-only
			STATUS	current
			::= { hmWanMbus48 90 }

hmWanMbus48Value2A		OBJECT-TYPE
			SYNTAX	INTEGER
			MAX-ACCESS	read-only
			STATUS	current
			::= { hmWanMbus48 91 }

hmWanMbus48VIF2B		OBJECT-TYPE
			SYNTAX	INTEGER
			MAX-ACCESS	read-only
			STATUS	current
			::= { hmWanMbus48 92 }

hmWanMbus48Value2B		OBJECT-TYPE
			SYNTAX	INTEGER
			MAX-ACCESS	read-only
			STATUS	current
			::= { hmWanMbus48 93 }

hmWanMbus48VIF2C		OBJECT-TYPE
			SYNTAX	INTEGER
			MAX-ACCESS	read-only
			STATUS	current
			::= { hmWanMbus48 94 }

hmWanMbus48Value2C		OBJECT-TYPE
			SYNTAX	INTEGER
			MAX-ACCESS	read-only
			STATUS	current
			::= { hmWanMbus48 95 }

hmWanMbus48VIF2D		OBJECT-TYPE
			SYNTAX	INTEGER
			MAX-ACCESS	read-only
			STATUS	current
			::= { hmWanMbus48 96 }

hmWanMbus48Value2D		OBJECT-TYPE
			SYNTAX	INTEGER
			MAX-ACCESS	read-only
			STATUS	current
			::= { hmWanMbus48 97 }

hmWanMbus48VIF2E		OBJECT-TYPE
			SYNTAX	INTEGER
			MAX-ACCESS	read-only
			STATUS	current
			::= { hmWanMbus48 98 }

hmWanMbus48Value2E		OBJECT-TYPE
			SYNTAX	INTEGER
			MAX-ACCESS	read-only
			STATUS	current
			::= { hmWanMbus48 99 }

hmWanMbus48VIF2F		OBJECT-TYPE
			SYNTAX	INTEGER
			MAX-ACCESS	read-only
			STATUS	current
			::= { hmWanMbus48 100 }

hmWanMbus48Value2F		OBJECT-TYPE
			SYNTAX	INTEGER
			MAX-ACCESS	read-only
			STATUS	current
			::= { hmWanMbus48 101 }

hmWanMbus49			OBJECT IDENTIFIER ::= { hmWanMbus 73 }

hmWanMbus49IdNumber		OBJECT-TYPE
			SYNTAX	Gauge32
			MAX-ACCESS	read-only
			STATUS	current
			::= { hmWanMbus49 1 }

hmWanMbus49Manufacturer	OBJECT-TYPE
			SYNTAX	Gauge32
			MAX-ACCESS	read-only
			STATUS	current
			::= { hmWanMbus49 2 }

hmWanMbus49Version		OBJECT-TYPE
			SYNTAX	Gauge32
			MAX-ACCESS	read-only
			STATUS	current
			::= { hmWanMbus49 3 }

hmWanMbus49Medium		OBJECT-TYPE
			SYNTAX	Gauge32
			MAX-ACCESS	read-only
			STATUS	current
			::= { hmWanMbus49 4 }

hmWanMbus49Status		OBJECT-TYPE
			SYNTAX	Gauge32
			MAX-ACCESS	read-only
			STATUS	current
			::= { hmWanMbus49 5 }

hmWanMbus49VIF00		OBJECT-TYPE
			SYNTAX	INTEGER
			MAX-ACCESS	read-only
			STATUS	current
			::= { hmWanMbus49 6 }

hmWanMbus49Value00		OBJECT-TYPE
			SYNTAX	INTEGER
			MAX-ACCESS	read-only
			STATUS	current
			::= { hmWanMbus49 7 }

hmWanMbus49VIF01		OBJECT-TYPE
			SYNTAX	INTEGER
			MAX-ACCESS	read-only
			STATUS	current
			::= { hmWanMbus49 8 }

hmWanMbus49Value01		OBJECT-TYPE
			SYNTAX	INTEGER
			MAX-ACCESS	read-only
			STATUS	current
			::= { hmWanMbus49 9 }

hmWanMbus49VIF02		OBJECT-TYPE
			SYNTAX	INTEGER
			MAX-ACCESS	read-only
			STATUS	current
			::= { hmWanMbus49 10 }

hmWanMbus49Value02		OBJECT-TYPE
			SYNTAX	INTEGER
			MAX-ACCESS	read-only
			STATUS	current
			::= { hmWanMbus49 11 }

hmWanMbus49VIF03		OBJECT-TYPE
			SYNTAX	INTEGER
			MAX-ACCESS	read-only
			STATUS	current
			::= { hmWanMbus49 12 }

hmWanMbus49Value03		OBJECT-TYPE
			SYNTAX	INTEGER
			MAX-ACCESS	read-only
			STATUS	current
			::= { hmWanMbus49 13 }

hmWanMbus49VIF04		OBJECT-TYPE
			SYNTAX	INTEGER
			MAX-ACCESS	read-only
			STATUS	current
			::= { hmWanMbus49 14 }

hmWanMbus49Value04		OBJECT-TYPE
			SYNTAX	INTEGER
			MAX-ACCESS	read-only
			STATUS	current
			::= { hmWanMbus49 15 }

hmWanMbus49VIF05		OBJECT-TYPE
			SYNTAX	INTEGER
			MAX-ACCESS	read-only
			STATUS	current
			::= { hmWanMbus49 16 }

hmWanMbus49Value05		OBJECT-TYPE
			SYNTAX	INTEGER
			MAX-ACCESS	read-only
			STATUS	current
			::= { hmWanMbus49 17 }

hmWanMbus49VIF06		OBJECT-TYPE
			SYNTAX	INTEGER
			MAX-ACCESS	read-only
			STATUS	current
			::= { hmWanMbus49 18 }

hmWanMbus49Value06		OBJECT-TYPE
			SYNTAX	INTEGER
			MAX-ACCESS	read-only
			STATUS	current
			::= { hmWanMbus49 19 }

hmWanMbus49VIF07		OBJECT-TYPE
			SYNTAX	INTEGER
			MAX-ACCESS	read-only
			STATUS	current
			::= { hmWanMbus49 20 }

hmWanMbus49Value07		OBJECT-TYPE
			SYNTAX	INTEGER
			MAX-ACCESS	read-only
			STATUS	current
			::= { hmWanMbus49 21 }

hmWanMbus49VIF08		OBJECT-TYPE
			SYNTAX	INTEGER
			MAX-ACCESS	read-only
			STATUS	current
			::= { hmWanMbus49 22 }

hmWanMbus49Value08		OBJECT-TYPE
			SYNTAX	INTEGER
			MAX-ACCESS	read-only
			STATUS	current
			::= { hmWanMbus49 23 }

hmWanMbus49VIF09		OBJECT-TYPE
			SYNTAX	INTEGER
			MAX-ACCESS	read-only
			STATUS	current
			::= { hmWanMbus49 24 }

hmWanMbus49Value09		OBJECT-TYPE
			SYNTAX	INTEGER
			MAX-ACCESS	read-only
			STATUS	current
			::= { hmWanMbus49 25 }

hmWanMbus49VIF0A		OBJECT-TYPE
			SYNTAX	INTEGER
			MAX-ACCESS	read-only
			STATUS	current
			::= { hmWanMbus49 26 }

hmWanMbus49Value0A		OBJECT-TYPE
			SYNTAX	INTEGER
			MAX-ACCESS	read-only
			STATUS	current
			::= { hmWanMbus49 27 }

hmWanMbus49VIF0B		OBJECT-TYPE
			SYNTAX	INTEGER
			MAX-ACCESS	read-only
			STATUS	current
			::= { hmWanMbus49 28 }

hmWanMbus49Value0B		OBJECT-TYPE
			SYNTAX	INTEGER
			MAX-ACCESS	read-only
			STATUS	current
			::= { hmWanMbus49 29 }

hmWanMbus49VIF0C		OBJECT-TYPE
			SYNTAX	INTEGER
			MAX-ACCESS	read-only
			STATUS	current
			::= { hmWanMbus49 30 }

hmWanMbus49Value0C		OBJECT-TYPE
			SYNTAX	INTEGER
			MAX-ACCESS	read-only
			STATUS	current
			::= { hmWanMbus49 31 }

hmWanMbus49VIF0D		OBJECT-TYPE
			SYNTAX	INTEGER
			MAX-ACCESS	read-only
			STATUS	current
			::= { hmWanMbus49 32 }

hmWanMbus49Value0D		OBJECT-TYPE
			SYNTAX	INTEGER
			MAX-ACCESS	read-only
			STATUS	current
			::= { hmWanMbus49 33 }

hmWanMbus49VIF0E		OBJECT-TYPE
			SYNTAX	INTEGER
			MAX-ACCESS	read-only
			STATUS	current
			::= { hmWanMbus49 34 }

hmWanMbus49Value0E		OBJECT-TYPE
			SYNTAX	INTEGER
			MAX-ACCESS	read-only
			STATUS	current
			::= { hmWanMbus49 35 }

hmWanMbus49VIF0F		OBJECT-TYPE
			SYNTAX	INTEGER
			MAX-ACCESS	read-only
			STATUS	current
			::= { hmWanMbus49 36 }

hmWanMbus49Value0F		OBJECT-TYPE
			SYNTAX	INTEGER
			MAX-ACCESS	read-only
			STATUS	current
			::= { hmWanMbus49 37 }

hmWanMbus49VIF10		OBJECT-TYPE
			SYNTAX	INTEGER
			MAX-ACCESS	read-only
			STATUS	current
			::= { hmWanMbus49 38 }

hmWanMbus49Value10		OBJECT-TYPE
			SYNTAX	INTEGER
			MAX-ACCESS	read-only
			STATUS	current
			::= { hmWanMbus49 39 }

hmWanMbus49VIF11		OBJECT-TYPE
			SYNTAX	INTEGER
			MAX-ACCESS	read-only
			STATUS	current
			::= { hmWanMbus49 40 }

hmWanMbus49Value11		OBJECT-TYPE
			SYNTAX	INTEGER
			MAX-ACCESS	read-only
			STATUS	current
			::= { hmWanMbus49 41 }

hmWanMbus49VIF12		OBJECT-TYPE
			SYNTAX	INTEGER
			MAX-ACCESS	read-only
			STATUS	current
			::= { hmWanMbus49 42 }

hmWanMbus49Value12		OBJECT-TYPE
			SYNTAX	INTEGER
			MAX-ACCESS	read-only
			STATUS	current
			::= { hmWanMbus49 43 }

hmWanMbus49VIF13		OBJECT-TYPE
			SYNTAX	INTEGER
			MAX-ACCESS	read-only
			STATUS	current
			::= { hmWanMbus49 44 }

hmWanMbus49Value13		OBJECT-TYPE
			SYNTAX	INTEGER
			MAX-ACCESS	read-only
			STATUS	current
			::= { hmWanMbus49 45 }

hmWanMbus49VIF14		OBJECT-TYPE
			SYNTAX	INTEGER
			MAX-ACCESS	read-only
			STATUS	current
			::= { hmWanMbus49 46 }

hmWanMbus49Value14		OBJECT-TYPE
			SYNTAX	INTEGER
			MAX-ACCESS	read-only
			STATUS	current
			::= { hmWanMbus49 47 }

hmWanMbus49VIF15		OBJECT-TYPE
			SYNTAX	INTEGER
			MAX-ACCESS	read-only
			STATUS	current
			::= { hmWanMbus49 48 }

hmWanMbus49Value15		OBJECT-TYPE
			SYNTAX	INTEGER
			MAX-ACCESS	read-only
			STATUS	current
			::= { hmWanMbus49 49 }

hmWanMbus49VIF16		OBJECT-TYPE
			SYNTAX	INTEGER
			MAX-ACCESS	read-only
			STATUS	current
			::= { hmWanMbus49 50 }

hmWanMbus49Value16		OBJECT-TYPE
			SYNTAX	INTEGER
			MAX-ACCESS	read-only
			STATUS	current
			::= { hmWanMbus49 51 }

hmWanMbus49VIF17		OBJECT-TYPE
			SYNTAX	INTEGER
			MAX-ACCESS	read-only
			STATUS	current
			::= { hmWanMbus49 52 }

hmWanMbus49Value17		OBJECT-TYPE
			SYNTAX	INTEGER
			MAX-ACCESS	read-only
			STATUS	current
			::= { hmWanMbus49 53 }

hmWanMbus49VIF18		OBJECT-TYPE
			SYNTAX	INTEGER
			MAX-ACCESS	read-only
			STATUS	current
			::= { hmWanMbus49 54 }

hmWanMbus49Value18		OBJECT-TYPE
			SYNTAX	INTEGER
			MAX-ACCESS	read-only
			STATUS	current
			::= { hmWanMbus49 55 }

hmWanMbus49VIF19		OBJECT-TYPE
			SYNTAX	INTEGER
			MAX-ACCESS	read-only
			STATUS	current
			::= { hmWanMbus49 56 }

hmWanMbus49Value19		OBJECT-TYPE
			SYNTAX	INTEGER
			MAX-ACCESS	read-only
			STATUS	current
			::= { hmWanMbus49 57 }

hmWanMbus49VIF1A		OBJECT-TYPE
			SYNTAX	INTEGER
			MAX-ACCESS	read-only
			STATUS	current
			::= { hmWanMbus49 58 }

hmWanMbus49Value1A		OBJECT-TYPE
			SYNTAX	INTEGER
			MAX-ACCESS	read-only
			STATUS	current
			::= { hmWanMbus49 59 }

hmWanMbus49VIF1B		OBJECT-TYPE
			SYNTAX	INTEGER
			MAX-ACCESS	read-only
			STATUS	current
			::= { hmWanMbus49 60 }

hmWanMbus49Value1B		OBJECT-TYPE
			SYNTAX	INTEGER
			MAX-ACCESS	read-only
			STATUS	current
			::= { hmWanMbus49 61 }

hmWanMbus49VIF1C		OBJECT-TYPE
			SYNTAX	INTEGER
			MAX-ACCESS	read-only
			STATUS	current
			::= { hmWanMbus49 62 }

hmWanMbus49Value1C		OBJECT-TYPE
			SYNTAX	INTEGER
			MAX-ACCESS	read-only
			STATUS	current
			::= { hmWanMbus49 63 }

hmWanMbus49VIF1D		OBJECT-TYPE
			SYNTAX	INTEGER
			MAX-ACCESS	read-only
			STATUS	current
			::= { hmWanMbus49 64 }

hmWanMbus49Value1D		OBJECT-TYPE
			SYNTAX	INTEGER
			MAX-ACCESS	read-only
			STATUS	current
			::= { hmWanMbus49 65 }

hmWanMbus49VIF1E		OBJECT-TYPE
			SYNTAX	INTEGER
			MAX-ACCESS	read-only
			STATUS	current
			::= { hmWanMbus49 66 }

hmWanMbus49Value1E		OBJECT-TYPE
			SYNTAX	INTEGER
			MAX-ACCESS	read-only
			STATUS	current
			::= { hmWanMbus49 67 }

hmWanMbus49VIF1F		OBJECT-TYPE
			SYNTAX	INTEGER
			MAX-ACCESS	read-only
			STATUS	current
			::= { hmWanMbus49 68 }

hmWanMbus49Value1F		OBJECT-TYPE
			SYNTAX	INTEGER
			MAX-ACCESS	read-only
			STATUS	current
			::= { hmWanMbus49 69 }

hmWanMbus49VIF20		OBJECT-TYPE
			SYNTAX	INTEGER
			MAX-ACCESS	read-only
			STATUS	current
			::= { hmWanMbus49 70 }

hmWanMbus49Value20		OBJECT-TYPE
			SYNTAX	INTEGER
			MAX-ACCESS	read-only
			STATUS	current
			::= { hmWanMbus49 71 }

hmWanMbus49VIF21		OBJECT-TYPE
			SYNTAX	INTEGER
			MAX-ACCESS	read-only
			STATUS	current
			::= { hmWanMbus49 72 }

hmWanMbus49Value21		OBJECT-TYPE
			SYNTAX	INTEGER
			MAX-ACCESS	read-only
			STATUS	current
			::= { hmWanMbus49 73 }

hmWanMbus49VIF22		OBJECT-TYPE
			SYNTAX	INTEGER
			MAX-ACCESS	read-only
			STATUS	current
			::= { hmWanMbus49 74 }

hmWanMbus49Value22		OBJECT-TYPE
			SYNTAX	INTEGER
			MAX-ACCESS	read-only
			STATUS	current
			::= { hmWanMbus49 75 }

hmWanMbus49VIF23		OBJECT-TYPE
			SYNTAX	INTEGER
			MAX-ACCESS	read-only
			STATUS	current
			::= { hmWanMbus49 76 }

hmWanMbus49Value23		OBJECT-TYPE
			SYNTAX	INTEGER
			MAX-ACCESS	read-only
			STATUS	current
			::= { hmWanMbus49 77 }

hmWanMbus49VIF24		OBJECT-TYPE
			SYNTAX	INTEGER
			MAX-ACCESS	read-only
			STATUS	current
			::= { hmWanMbus49 78 }

hmWanMbus49Value24		OBJECT-TYPE
			SYNTAX	INTEGER
			MAX-ACCESS	read-only
			STATUS	current
			::= { hmWanMbus49 79 }

hmWanMbus49VIF25		OBJECT-TYPE
			SYNTAX	INTEGER
			MAX-ACCESS	read-only
			STATUS	current
			::= { hmWanMbus49 80 }

hmWanMbus49Value25		OBJECT-TYPE
			SYNTAX	INTEGER
			MAX-ACCESS	read-only
			STATUS	current
			::= { hmWanMbus49 81 }

hmWanMbus49VIF26		OBJECT-TYPE
			SYNTAX	INTEGER
			MAX-ACCESS	read-only
			STATUS	current
			::= { hmWanMbus49 82 }

hmWanMbus49Value26		OBJECT-TYPE
			SYNTAX	INTEGER
			MAX-ACCESS	read-only
			STATUS	current
			::= { hmWanMbus49 83 }

hmWanMbus49VIF27		OBJECT-TYPE
			SYNTAX	INTEGER
			MAX-ACCESS	read-only
			STATUS	current
			::= { hmWanMbus49 84 }

hmWanMbus49Value27		OBJECT-TYPE
			SYNTAX	INTEGER
			MAX-ACCESS	read-only
			STATUS	current
			::= { hmWanMbus49 85 }

hmWanMbus49VIF28		OBJECT-TYPE
			SYNTAX	INTEGER
			MAX-ACCESS	read-only
			STATUS	current
			::= { hmWanMbus49 86 }

hmWanMbus49Value28		OBJECT-TYPE
			SYNTAX	INTEGER
			MAX-ACCESS	read-only
			STATUS	current
			::= { hmWanMbus49 87 }

hmWanMbus49VIF29		OBJECT-TYPE
			SYNTAX	INTEGER
			MAX-ACCESS	read-only
			STATUS	current
			::= { hmWanMbus49 88 }

hmWanMbus49Value29		OBJECT-TYPE
			SYNTAX	INTEGER
			MAX-ACCESS	read-only
			STATUS	current
			::= { hmWanMbus49 89 }

hmWanMbus49VIF2A		OBJECT-TYPE
			SYNTAX	INTEGER
			MAX-ACCESS	read-only
			STATUS	current
			::= { hmWanMbus49 90 }

hmWanMbus49Value2A		OBJECT-TYPE
			SYNTAX	INTEGER
			MAX-ACCESS	read-only
			STATUS	current
			::= { hmWanMbus49 91 }

hmWanMbus49VIF2B		OBJECT-TYPE
			SYNTAX	INTEGER
			MAX-ACCESS	read-only
			STATUS	current
			::= { hmWanMbus49 92 }

hmWanMbus49Value2B		OBJECT-TYPE
			SYNTAX	INTEGER
			MAX-ACCESS	read-only
			STATUS	current
			::= { hmWanMbus49 93 }

hmWanMbus49VIF2C		OBJECT-TYPE
			SYNTAX	INTEGER
			MAX-ACCESS	read-only
			STATUS	current
			::= { hmWanMbus49 94 }

hmWanMbus49Value2C		OBJECT-TYPE
			SYNTAX	INTEGER
			MAX-ACCESS	read-only
			STATUS	current
			::= { hmWanMbus49 95 }

hmWanMbus49VIF2D		OBJECT-TYPE
			SYNTAX	INTEGER
			MAX-ACCESS	read-only
			STATUS	current
			::= { hmWanMbus49 96 }

hmWanMbus49Value2D		OBJECT-TYPE
			SYNTAX	INTEGER
			MAX-ACCESS	read-only
			STATUS	current
			::= { hmWanMbus49 97 }

hmWanMbus49VIF2E		OBJECT-TYPE
			SYNTAX	INTEGER
			MAX-ACCESS	read-only
			STATUS	current
			::= { hmWanMbus49 98 }

hmWanMbus49Value2E		OBJECT-TYPE
			SYNTAX	INTEGER
			MAX-ACCESS	read-only
			STATUS	current
			::= { hmWanMbus49 99 }

hmWanMbus49VIF2F		OBJECT-TYPE
			SYNTAX	INTEGER
			MAX-ACCESS	read-only
			STATUS	current
			::= { hmWanMbus49 100 }

hmWanMbus49Value2F		OBJECT-TYPE
			SYNTAX	INTEGER
			MAX-ACCESS	read-only
			STATUS	current
			::= { hmWanMbus49 101 }

hmWanMbus4A			OBJECT IDENTIFIER ::= { hmWanMbus 74 }

hmWanMbus4AIdNumber		OBJECT-TYPE
			SYNTAX	Gauge32
			MAX-ACCESS	read-only
			STATUS	current
			::= { hmWanMbus4A 1 }

hmWanMbus4AManufacturer	OBJECT-TYPE
			SYNTAX	Gauge32
			MAX-ACCESS	read-only
			STATUS	current
			::= { hmWanMbus4A 2 }

hmWanMbus4AVersion		OBJECT-TYPE
			SYNTAX	Gauge32
			MAX-ACCESS	read-only
			STATUS	current
			::= { hmWanMbus4A 3 }

hmWanMbus4AMedium		OBJECT-TYPE
			SYNTAX	Gauge32
			MAX-ACCESS	read-only
			STATUS	current
			::= { hmWanMbus4A 4 }

hmWanMbus4AStatus		OBJECT-TYPE
			SYNTAX	Gauge32
			MAX-ACCESS	read-only
			STATUS	current
			::= { hmWanMbus4A 5 }

hmWanMbus4AVIF00		OBJECT-TYPE
			SYNTAX	INTEGER
			MAX-ACCESS	read-only
			STATUS	current
			::= { hmWanMbus4A 6 }

hmWanMbus4AValue00		OBJECT-TYPE
			SYNTAX	INTEGER
			MAX-ACCESS	read-only
			STATUS	current
			::= { hmWanMbus4A 7 }

hmWanMbus4AVIF01		OBJECT-TYPE
			SYNTAX	INTEGER
			MAX-ACCESS	read-only
			STATUS	current
			::= { hmWanMbus4A 8 }

hmWanMbus4AValue01		OBJECT-TYPE
			SYNTAX	INTEGER
			MAX-ACCESS	read-only
			STATUS	current
			::= { hmWanMbus4A 9 }

hmWanMbus4AVIF02		OBJECT-TYPE
			SYNTAX	INTEGER
			MAX-ACCESS	read-only
			STATUS	current
			::= { hmWanMbus4A 10 }

hmWanMbus4AValue02		OBJECT-TYPE
			SYNTAX	INTEGER
			MAX-ACCESS	read-only
			STATUS	current
			::= { hmWanMbus4A 11 }

hmWanMbus4AVIF03		OBJECT-TYPE
			SYNTAX	INTEGER
			MAX-ACCESS	read-only
			STATUS	current
			::= { hmWanMbus4A 12 }

hmWanMbus4AValue03		OBJECT-TYPE
			SYNTAX	INTEGER
			MAX-ACCESS	read-only
			STATUS	current
			::= { hmWanMbus4A 13 }

hmWanMbus4AVIF04		OBJECT-TYPE
			SYNTAX	INTEGER
			MAX-ACCESS	read-only
			STATUS	current
			::= { hmWanMbus4A 14 }

hmWanMbus4AValue04		OBJECT-TYPE
			SYNTAX	INTEGER
			MAX-ACCESS	read-only
			STATUS	current
			::= { hmWanMbus4A 15 }

hmWanMbus4AVIF05		OBJECT-TYPE
			SYNTAX	INTEGER
			MAX-ACCESS	read-only
			STATUS	current
			::= { hmWanMbus4A 16 }

hmWanMbus4AValue05		OBJECT-TYPE
			SYNTAX	INTEGER
			MAX-ACCESS	read-only
			STATUS	current
			::= { hmWanMbus4A 17 }

hmWanMbus4AVIF06		OBJECT-TYPE
			SYNTAX	INTEGER
			MAX-ACCESS	read-only
			STATUS	current
			::= { hmWanMbus4A 18 }

hmWanMbus4AValue06		OBJECT-TYPE
			SYNTAX	INTEGER
			MAX-ACCESS	read-only
			STATUS	current
			::= { hmWanMbus4A 19 }

hmWanMbus4AVIF07		OBJECT-TYPE
			SYNTAX	INTEGER
			MAX-ACCESS	read-only
			STATUS	current
			::= { hmWanMbus4A 20 }

hmWanMbus4AValue07		OBJECT-TYPE
			SYNTAX	INTEGER
			MAX-ACCESS	read-only
			STATUS	current
			::= { hmWanMbus4A 21 }

hmWanMbus4AVIF08		OBJECT-TYPE
			SYNTAX	INTEGER
			MAX-ACCESS	read-only
			STATUS	current
			::= { hmWanMbus4A 22 }

hmWanMbus4AValue08		OBJECT-TYPE
			SYNTAX	INTEGER
			MAX-ACCESS	read-only
			STATUS	current
			::= { hmWanMbus4A 23 }

hmWanMbus4AVIF09		OBJECT-TYPE
			SYNTAX	INTEGER
			MAX-ACCESS	read-only
			STATUS	current
			::= { hmWanMbus4A 24 }

hmWanMbus4AValue09		OBJECT-TYPE
			SYNTAX	INTEGER
			MAX-ACCESS	read-only
			STATUS	current
			::= { hmWanMbus4A 25 }

hmWanMbus4AVIF0A		OBJECT-TYPE
			SYNTAX	INTEGER
			MAX-ACCESS	read-only
			STATUS	current
			::= { hmWanMbus4A 26 }

hmWanMbus4AValue0A		OBJECT-TYPE
			SYNTAX	INTEGER
			MAX-ACCESS	read-only
			STATUS	current
			::= { hmWanMbus4A 27 }

hmWanMbus4AVIF0B		OBJECT-TYPE
			SYNTAX	INTEGER
			MAX-ACCESS	read-only
			STATUS	current
			::= { hmWanMbus4A 28 }

hmWanMbus4AValue0B		OBJECT-TYPE
			SYNTAX	INTEGER
			MAX-ACCESS	read-only
			STATUS	current
			::= { hmWanMbus4A 29 }

hmWanMbus4AVIF0C		OBJECT-TYPE
			SYNTAX	INTEGER
			MAX-ACCESS	read-only
			STATUS	current
			::= { hmWanMbus4A 30 }

hmWanMbus4AValue0C		OBJECT-TYPE
			SYNTAX	INTEGER
			MAX-ACCESS	read-only
			STATUS	current
			::= { hmWanMbus4A 31 }

hmWanMbus4AVIF0D		OBJECT-TYPE
			SYNTAX	INTEGER
			MAX-ACCESS	read-only
			STATUS	current
			::= { hmWanMbus4A 32 }

hmWanMbus4AValue0D		OBJECT-TYPE
			SYNTAX	INTEGER
			MAX-ACCESS	read-only
			STATUS	current
			::= { hmWanMbus4A 33 }

hmWanMbus4AVIF0E		OBJECT-TYPE
			SYNTAX	INTEGER
			MAX-ACCESS	read-only
			STATUS	current
			::= { hmWanMbus4A 34 }

hmWanMbus4AValue0E		OBJECT-TYPE
			SYNTAX	INTEGER
			MAX-ACCESS	read-only
			STATUS	current
			::= { hmWanMbus4A 35 }

hmWanMbus4AVIF0F		OBJECT-TYPE
			SYNTAX	INTEGER
			MAX-ACCESS	read-only
			STATUS	current
			::= { hmWanMbus4A 36 }

hmWanMbus4AValue0F		OBJECT-TYPE
			SYNTAX	INTEGER
			MAX-ACCESS	read-only
			STATUS	current
			::= { hmWanMbus4A 37 }

hmWanMbus4AVIF10		OBJECT-TYPE
			SYNTAX	INTEGER
			MAX-ACCESS	read-only
			STATUS	current
			::= { hmWanMbus4A 38 }

hmWanMbus4AValue10		OBJECT-TYPE
			SYNTAX	INTEGER
			MAX-ACCESS	read-only
			STATUS	current
			::= { hmWanMbus4A 39 }

hmWanMbus4AVIF11		OBJECT-TYPE
			SYNTAX	INTEGER
			MAX-ACCESS	read-only
			STATUS	current
			::= { hmWanMbus4A 40 }

hmWanMbus4AValue11		OBJECT-TYPE
			SYNTAX	INTEGER
			MAX-ACCESS	read-only
			STATUS	current
			::= { hmWanMbus4A 41 }

hmWanMbus4AVIF12		OBJECT-TYPE
			SYNTAX	INTEGER
			MAX-ACCESS	read-only
			STATUS	current
			::= { hmWanMbus4A 42 }

hmWanMbus4AValue12		OBJECT-TYPE
			SYNTAX	INTEGER
			MAX-ACCESS	read-only
			STATUS	current
			::= { hmWanMbus4A 43 }

hmWanMbus4AVIF13		OBJECT-TYPE
			SYNTAX	INTEGER
			MAX-ACCESS	read-only
			STATUS	current
			::= { hmWanMbus4A 44 }

hmWanMbus4AValue13		OBJECT-TYPE
			SYNTAX	INTEGER
			MAX-ACCESS	read-only
			STATUS	current
			::= { hmWanMbus4A 45 }

hmWanMbus4AVIF14		OBJECT-TYPE
			SYNTAX	INTEGER
			MAX-ACCESS	read-only
			STATUS	current
			::= { hmWanMbus4A 46 }

hmWanMbus4AValue14		OBJECT-TYPE
			SYNTAX	INTEGER
			MAX-ACCESS	read-only
			STATUS	current
			::= { hmWanMbus4A 47 }

hmWanMbus4AVIF15		OBJECT-TYPE
			SYNTAX	INTEGER
			MAX-ACCESS	read-only
			STATUS	current
			::= { hmWanMbus4A 48 }

hmWanMbus4AValue15		OBJECT-TYPE
			SYNTAX	INTEGER
			MAX-ACCESS	read-only
			STATUS	current
			::= { hmWanMbus4A 49 }

hmWanMbus4AVIF16		OBJECT-TYPE
			SYNTAX	INTEGER
			MAX-ACCESS	read-only
			STATUS	current
			::= { hmWanMbus4A 50 }

hmWanMbus4AValue16		OBJECT-TYPE
			SYNTAX	INTEGER
			MAX-ACCESS	read-only
			STATUS	current
			::= { hmWanMbus4A 51 }

hmWanMbus4AVIF17		OBJECT-TYPE
			SYNTAX	INTEGER
			MAX-ACCESS	read-only
			STATUS	current
			::= { hmWanMbus4A 52 }

hmWanMbus4AValue17		OBJECT-TYPE
			SYNTAX	INTEGER
			MAX-ACCESS	read-only
			STATUS	current
			::= { hmWanMbus4A 53 }

hmWanMbus4AVIF18		OBJECT-TYPE
			SYNTAX	INTEGER
			MAX-ACCESS	read-only
			STATUS	current
			::= { hmWanMbus4A 54 }

hmWanMbus4AValue18		OBJECT-TYPE
			SYNTAX	INTEGER
			MAX-ACCESS	read-only
			STATUS	current
			::= { hmWanMbus4A 55 }

hmWanMbus4AVIF19		OBJECT-TYPE
			SYNTAX	INTEGER
			MAX-ACCESS	read-only
			STATUS	current
			::= { hmWanMbus4A 56 }

hmWanMbus4AValue19		OBJECT-TYPE
			SYNTAX	INTEGER
			MAX-ACCESS	read-only
			STATUS	current
			::= { hmWanMbus4A 57 }

hmWanMbus4AVIF1A		OBJECT-TYPE
			SYNTAX	INTEGER
			MAX-ACCESS	read-only
			STATUS	current
			::= { hmWanMbus4A 58 }

hmWanMbus4AValue1A		OBJECT-TYPE
			SYNTAX	INTEGER
			MAX-ACCESS	read-only
			STATUS	current
			::= { hmWanMbus4A 59 }

hmWanMbus4AVIF1B		OBJECT-TYPE
			SYNTAX	INTEGER
			MAX-ACCESS	read-only
			STATUS	current
			::= { hmWanMbus4A 60 }

hmWanMbus4AValue1B		OBJECT-TYPE
			SYNTAX	INTEGER
			MAX-ACCESS	read-only
			STATUS	current
			::= { hmWanMbus4A 61 }

hmWanMbus4AVIF1C		OBJECT-TYPE
			SYNTAX	INTEGER
			MAX-ACCESS	read-only
			STATUS	current
			::= { hmWanMbus4A 62 }

hmWanMbus4AValue1C		OBJECT-TYPE
			SYNTAX	INTEGER
			MAX-ACCESS	read-only
			STATUS	current
			::= { hmWanMbus4A 63 }

hmWanMbus4AVIF1D		OBJECT-TYPE
			SYNTAX	INTEGER
			MAX-ACCESS	read-only
			STATUS	current
			::= { hmWanMbus4A 64 }

hmWanMbus4AValue1D		OBJECT-TYPE
			SYNTAX	INTEGER
			MAX-ACCESS	read-only
			STATUS	current
			::= { hmWanMbus4A 65 }

hmWanMbus4AVIF1E		OBJECT-TYPE
			SYNTAX	INTEGER
			MAX-ACCESS	read-only
			STATUS	current
			::= { hmWanMbus4A 66 }

hmWanMbus4AValue1E		OBJECT-TYPE
			SYNTAX	INTEGER
			MAX-ACCESS	read-only
			STATUS	current
			::= { hmWanMbus4A 67 }

hmWanMbus4AVIF1F		OBJECT-TYPE
			SYNTAX	INTEGER
			MAX-ACCESS	read-only
			STATUS	current
			::= { hmWanMbus4A 68 }

hmWanMbus4AValue1F		OBJECT-TYPE
			SYNTAX	INTEGER
			MAX-ACCESS	read-only
			STATUS	current
			::= { hmWanMbus4A 69 }

hmWanMbus4AVIF20		OBJECT-TYPE
			SYNTAX	INTEGER
			MAX-ACCESS	read-only
			STATUS	current
			::= { hmWanMbus4A 70 }

hmWanMbus4AValue20		OBJECT-TYPE
			SYNTAX	INTEGER
			MAX-ACCESS	read-only
			STATUS	current
			::= { hmWanMbus4A 71 }

hmWanMbus4AVIF21		OBJECT-TYPE
			SYNTAX	INTEGER
			MAX-ACCESS	read-only
			STATUS	current
			::= { hmWanMbus4A 72 }

hmWanMbus4AValue21		OBJECT-TYPE
			SYNTAX	INTEGER
			MAX-ACCESS	read-only
			STATUS	current
			::= { hmWanMbus4A 73 }

hmWanMbus4AVIF22		OBJECT-TYPE
			SYNTAX	INTEGER
			MAX-ACCESS	read-only
			STATUS	current
			::= { hmWanMbus4A 74 }

hmWanMbus4AValue22		OBJECT-TYPE
			SYNTAX	INTEGER
			MAX-ACCESS	read-only
			STATUS	current
			::= { hmWanMbus4A 75 }

hmWanMbus4AVIF23		OBJECT-TYPE
			SYNTAX	INTEGER
			MAX-ACCESS	read-only
			STATUS	current
			::= { hmWanMbus4A 76 }

hmWanMbus4AValue23		OBJECT-TYPE
			SYNTAX	INTEGER
			MAX-ACCESS	read-only
			STATUS	current
			::= { hmWanMbus4A 77 }

hmWanMbus4AVIF24		OBJECT-TYPE
			SYNTAX	INTEGER
			MAX-ACCESS	read-only
			STATUS	current
			::= { hmWanMbus4A 78 }

hmWanMbus4AValue24		OBJECT-TYPE
			SYNTAX	INTEGER
			MAX-ACCESS	read-only
			STATUS	current
			::= { hmWanMbus4A 79 }

hmWanMbus4AVIF25		OBJECT-TYPE
			SYNTAX	INTEGER
			MAX-ACCESS	read-only
			STATUS	current
			::= { hmWanMbus4A 80 }

hmWanMbus4AValue25		OBJECT-TYPE
			SYNTAX	INTEGER
			MAX-ACCESS	read-only
			STATUS	current
			::= { hmWanMbus4A 81 }

hmWanMbus4AVIF26		OBJECT-TYPE
			SYNTAX	INTEGER
			MAX-ACCESS	read-only
			STATUS	current
			::= { hmWanMbus4A 82 }

hmWanMbus4AValue26		OBJECT-TYPE
			SYNTAX	INTEGER
			MAX-ACCESS	read-only
			STATUS	current
			::= { hmWanMbus4A 83 }

hmWanMbus4AVIF27		OBJECT-TYPE
			SYNTAX	INTEGER
			MAX-ACCESS	read-only
			STATUS	current
			::= { hmWanMbus4A 84 }

hmWanMbus4AValue27		OBJECT-TYPE
			SYNTAX	INTEGER
			MAX-ACCESS	read-only
			STATUS	current
			::= { hmWanMbus4A 85 }

hmWanMbus4AVIF28		OBJECT-TYPE
			SYNTAX	INTEGER
			MAX-ACCESS	read-only
			STATUS	current
			::= { hmWanMbus4A 86 }

hmWanMbus4AValue28		OBJECT-TYPE
			SYNTAX	INTEGER
			MAX-ACCESS	read-only
			STATUS	current
			::= { hmWanMbus4A 87 }

hmWanMbus4AVIF29		OBJECT-TYPE
			SYNTAX	INTEGER
			MAX-ACCESS	read-only
			STATUS	current
			::= { hmWanMbus4A 88 }

hmWanMbus4AValue29		OBJECT-TYPE
			SYNTAX	INTEGER
			MAX-ACCESS	read-only
			STATUS	current
			::= { hmWanMbus4A 89 }

hmWanMbus4AVIF2A		OBJECT-TYPE
			SYNTAX	INTEGER
			MAX-ACCESS	read-only
			STATUS	current
			::= { hmWanMbus4A 90 }

hmWanMbus4AValue2A		OBJECT-TYPE
			SYNTAX	INTEGER
			MAX-ACCESS	read-only
			STATUS	current
			::= { hmWanMbus4A 91 }

hmWanMbus4AVIF2B		OBJECT-TYPE
			SYNTAX	INTEGER
			MAX-ACCESS	read-only
			STATUS	current
			::= { hmWanMbus4A 92 }

hmWanMbus4AValue2B		OBJECT-TYPE
			SYNTAX	INTEGER
			MAX-ACCESS	read-only
			STATUS	current
			::= { hmWanMbus4A 93 }

hmWanMbus4AVIF2C		OBJECT-TYPE
			SYNTAX	INTEGER
			MAX-ACCESS	read-only
			STATUS	current
			::= { hmWanMbus4A 94 }

hmWanMbus4AValue2C		OBJECT-TYPE
			SYNTAX	INTEGER
			MAX-ACCESS	read-only
			STATUS	current
			::= { hmWanMbus4A 95 }

hmWanMbus4AVIF2D		OBJECT-TYPE
			SYNTAX	INTEGER
			MAX-ACCESS	read-only
			STATUS	current
			::= { hmWanMbus4A 96 }

hmWanMbus4AValue2D		OBJECT-TYPE
			SYNTAX	INTEGER
			MAX-ACCESS	read-only
			STATUS	current
			::= { hmWanMbus4A 97 }

hmWanMbus4AVIF2E		OBJECT-TYPE
			SYNTAX	INTEGER
			MAX-ACCESS	read-only
			STATUS	current
			::= { hmWanMbus4A 98 }

hmWanMbus4AValue2E		OBJECT-TYPE
			SYNTAX	INTEGER
			MAX-ACCESS	read-only
			STATUS	current
			::= { hmWanMbus4A 99 }

hmWanMbus4AVIF2F		OBJECT-TYPE
			SYNTAX	INTEGER
			MAX-ACCESS	read-only
			STATUS	current
			::= { hmWanMbus4A 100 }

hmWanMbus4AValue2F		OBJECT-TYPE
			SYNTAX	INTEGER
			MAX-ACCESS	read-only
			STATUS	current
			::= { hmWanMbus4A 101 }

hmWanMbus4B			OBJECT IDENTIFIER ::= { hmWanMbus 75 }

hmWanMbus4BIdNumber		OBJECT-TYPE
			SYNTAX	Gauge32
			MAX-ACCESS	read-only
			STATUS	current
			::= { hmWanMbus4B 1 }

hmWanMbus4BManufacturer	OBJECT-TYPE
			SYNTAX	Gauge32
			MAX-ACCESS	read-only
			STATUS	current
			::= { hmWanMbus4B 2 }

hmWanMbus4BVersion		OBJECT-TYPE
			SYNTAX	Gauge32
			MAX-ACCESS	read-only
			STATUS	current
			::= { hmWanMbus4B 3 }

hmWanMbus4BMedium		OBJECT-TYPE
			SYNTAX	Gauge32
			MAX-ACCESS	read-only
			STATUS	current
			::= { hmWanMbus4B 4 }

hmWanMbus4BStatus		OBJECT-TYPE
			SYNTAX	Gauge32
			MAX-ACCESS	read-only
			STATUS	current
			::= { hmWanMbus4B 5 }

hmWanMbus4BVIF00		OBJECT-TYPE
			SYNTAX	INTEGER
			MAX-ACCESS	read-only
			STATUS	current
			::= { hmWanMbus4B 6 }

hmWanMbus4BValue00		OBJECT-TYPE
			SYNTAX	INTEGER
			MAX-ACCESS	read-only
			STATUS	current
			::= { hmWanMbus4B 7 }

hmWanMbus4BVIF01		OBJECT-TYPE
			SYNTAX	INTEGER
			MAX-ACCESS	read-only
			STATUS	current
			::= { hmWanMbus4B 8 }

hmWanMbus4BValue01		OBJECT-TYPE
			SYNTAX	INTEGER
			MAX-ACCESS	read-only
			STATUS	current
			::= { hmWanMbus4B 9 }

hmWanMbus4BVIF02		OBJECT-TYPE
			SYNTAX	INTEGER
			MAX-ACCESS	read-only
			STATUS	current
			::= { hmWanMbus4B 10 }

hmWanMbus4BValue02		OBJECT-TYPE
			SYNTAX	INTEGER
			MAX-ACCESS	read-only
			STATUS	current
			::= { hmWanMbus4B 11 }

hmWanMbus4BVIF03		OBJECT-TYPE
			SYNTAX	INTEGER
			MAX-ACCESS	read-only
			STATUS	current
			::= { hmWanMbus4B 12 }

hmWanMbus4BValue03		OBJECT-TYPE
			SYNTAX	INTEGER
			MAX-ACCESS	read-only
			STATUS	current
			::= { hmWanMbus4B 13 }

hmWanMbus4BVIF04		OBJECT-TYPE
			SYNTAX	INTEGER
			MAX-ACCESS	read-only
			STATUS	current
			::= { hmWanMbus4B 14 }

hmWanMbus4BValue04		OBJECT-TYPE
			SYNTAX	INTEGER
			MAX-ACCESS	read-only
			STATUS	current
			::= { hmWanMbus4B 15 }

hmWanMbus4BVIF05		OBJECT-TYPE
			SYNTAX	INTEGER
			MAX-ACCESS	read-only
			STATUS	current
			::= { hmWanMbus4B 16 }

hmWanMbus4BValue05		OBJECT-TYPE
			SYNTAX	INTEGER
			MAX-ACCESS	read-only
			STATUS	current
			::= { hmWanMbus4B 17 }

hmWanMbus4BVIF06		OBJECT-TYPE
			SYNTAX	INTEGER
			MAX-ACCESS	read-only
			STATUS	current
			::= { hmWanMbus4B 18 }

hmWanMbus4BValue06		OBJECT-TYPE
			SYNTAX	INTEGER
			MAX-ACCESS	read-only
			STATUS	current
			::= { hmWanMbus4B 19 }

hmWanMbus4BVIF07		OBJECT-TYPE
			SYNTAX	INTEGER
			MAX-ACCESS	read-only
			STATUS	current
			::= { hmWanMbus4B 20 }

hmWanMbus4BValue07		OBJECT-TYPE
			SYNTAX	INTEGER
			MAX-ACCESS	read-only
			STATUS	current
			::= { hmWanMbus4B 21 }

hmWanMbus4BVIF08		OBJECT-TYPE
			SYNTAX	INTEGER
			MAX-ACCESS	read-only
			STATUS	current
			::= { hmWanMbus4B 22 }

hmWanMbus4BValue08		OBJECT-TYPE
			SYNTAX	INTEGER
			MAX-ACCESS	read-only
			STATUS	current
			::= { hmWanMbus4B 23 }

hmWanMbus4BVIF09		OBJECT-TYPE
			SYNTAX	INTEGER
			MAX-ACCESS	read-only
			STATUS	current
			::= { hmWanMbus4B 24 }

hmWanMbus4BValue09		OBJECT-TYPE
			SYNTAX	INTEGER
			MAX-ACCESS	read-only
			STATUS	current
			::= { hmWanMbus4B 25 }

hmWanMbus4BVIF0A		OBJECT-TYPE
			SYNTAX	INTEGER
			MAX-ACCESS	read-only
			STATUS	current
			::= { hmWanMbus4B 26 }

hmWanMbus4BValue0A		OBJECT-TYPE
			SYNTAX	INTEGER
			MAX-ACCESS	read-only
			STATUS	current
			::= { hmWanMbus4B 27 }

hmWanMbus4BVIF0B		OBJECT-TYPE
			SYNTAX	INTEGER
			MAX-ACCESS	read-only
			STATUS	current
			::= { hmWanMbus4B 28 }

hmWanMbus4BValue0B		OBJECT-TYPE
			SYNTAX	INTEGER
			MAX-ACCESS	read-only
			STATUS	current
			::= { hmWanMbus4B 29 }

hmWanMbus4BVIF0C		OBJECT-TYPE
			SYNTAX	INTEGER
			MAX-ACCESS	read-only
			STATUS	current
			::= { hmWanMbus4B 30 }

hmWanMbus4BValue0C		OBJECT-TYPE
			SYNTAX	INTEGER
			MAX-ACCESS	read-only
			STATUS	current
			::= { hmWanMbus4B 31 }

hmWanMbus4BVIF0D		OBJECT-TYPE
			SYNTAX	INTEGER
			MAX-ACCESS	read-only
			STATUS	current
			::= { hmWanMbus4B 32 }

hmWanMbus4BValue0D		OBJECT-TYPE
			SYNTAX	INTEGER
			MAX-ACCESS	read-only
			STATUS	current
			::= { hmWanMbus4B 33 }

hmWanMbus4BVIF0E		OBJECT-TYPE
			SYNTAX	INTEGER
			MAX-ACCESS	read-only
			STATUS	current
			::= { hmWanMbus4B 34 }

hmWanMbus4BValue0E		OBJECT-TYPE
			SYNTAX	INTEGER
			MAX-ACCESS	read-only
			STATUS	current
			::= { hmWanMbus4B 35 }

hmWanMbus4BVIF0F		OBJECT-TYPE
			SYNTAX	INTEGER
			MAX-ACCESS	read-only
			STATUS	current
			::= { hmWanMbus4B 36 }

hmWanMbus4BValue0F		OBJECT-TYPE
			SYNTAX	INTEGER
			MAX-ACCESS	read-only
			STATUS	current
			::= { hmWanMbus4B 37 }

hmWanMbus4BVIF10		OBJECT-TYPE
			SYNTAX	INTEGER
			MAX-ACCESS	read-only
			STATUS	current
			::= { hmWanMbus4B 38 }

hmWanMbus4BValue10		OBJECT-TYPE
			SYNTAX	INTEGER
			MAX-ACCESS	read-only
			STATUS	current
			::= { hmWanMbus4B 39 }

hmWanMbus4BVIF11		OBJECT-TYPE
			SYNTAX	INTEGER
			MAX-ACCESS	read-only
			STATUS	current
			::= { hmWanMbus4B 40 }

hmWanMbus4BValue11		OBJECT-TYPE
			SYNTAX	INTEGER
			MAX-ACCESS	read-only
			STATUS	current
			::= { hmWanMbus4B 41 }

hmWanMbus4BVIF12		OBJECT-TYPE
			SYNTAX	INTEGER
			MAX-ACCESS	read-only
			STATUS	current
			::= { hmWanMbus4B 42 }

hmWanMbus4BValue12		OBJECT-TYPE
			SYNTAX	INTEGER
			MAX-ACCESS	read-only
			STATUS	current
			::= { hmWanMbus4B 43 }

hmWanMbus4BVIF13		OBJECT-TYPE
			SYNTAX	INTEGER
			MAX-ACCESS	read-only
			STATUS	current
			::= { hmWanMbus4B 44 }

hmWanMbus4BValue13		OBJECT-TYPE
			SYNTAX	INTEGER
			MAX-ACCESS	read-only
			STATUS	current
			::= { hmWanMbus4B 45 }

hmWanMbus4BVIF14		OBJECT-TYPE
			SYNTAX	INTEGER
			MAX-ACCESS	read-only
			STATUS	current
			::= { hmWanMbus4B 46 }

hmWanMbus4BValue14		OBJECT-TYPE
			SYNTAX	INTEGER
			MAX-ACCESS	read-only
			STATUS	current
			::= { hmWanMbus4B 47 }

hmWanMbus4BVIF15		OBJECT-TYPE
			SYNTAX	INTEGER
			MAX-ACCESS	read-only
			STATUS	current
			::= { hmWanMbus4B 48 }

hmWanMbus4BValue15		OBJECT-TYPE
			SYNTAX	INTEGER
			MAX-ACCESS	read-only
			STATUS	current
			::= { hmWanMbus4B 49 }

hmWanMbus4BVIF16		OBJECT-TYPE
			SYNTAX	INTEGER
			MAX-ACCESS	read-only
			STATUS	current
			::= { hmWanMbus4B 50 }

hmWanMbus4BValue16		OBJECT-TYPE
			SYNTAX	INTEGER
			MAX-ACCESS	read-only
			STATUS	current
			::= { hmWanMbus4B 51 }

hmWanMbus4BVIF17		OBJECT-TYPE
			SYNTAX	INTEGER
			MAX-ACCESS	read-only
			STATUS	current
			::= { hmWanMbus4B 52 }

hmWanMbus4BValue17		OBJECT-TYPE
			SYNTAX	INTEGER
			MAX-ACCESS	read-only
			STATUS	current
			::= { hmWanMbus4B 53 }

hmWanMbus4BVIF18		OBJECT-TYPE
			SYNTAX	INTEGER
			MAX-ACCESS	read-only
			STATUS	current
			::= { hmWanMbus4B 54 }

hmWanMbus4BValue18		OBJECT-TYPE
			SYNTAX	INTEGER
			MAX-ACCESS	read-only
			STATUS	current
			::= { hmWanMbus4B 55 }

hmWanMbus4BVIF19		OBJECT-TYPE
			SYNTAX	INTEGER
			MAX-ACCESS	read-only
			STATUS	current
			::= { hmWanMbus4B 56 }

hmWanMbus4BValue19		OBJECT-TYPE
			SYNTAX	INTEGER
			MAX-ACCESS	read-only
			STATUS	current
			::= { hmWanMbus4B 57 }

hmWanMbus4BVIF1A		OBJECT-TYPE
			SYNTAX	INTEGER
			MAX-ACCESS	read-only
			STATUS	current
			::= { hmWanMbus4B 58 }

hmWanMbus4BValue1A		OBJECT-TYPE
			SYNTAX	INTEGER
			MAX-ACCESS	read-only
			STATUS	current
			::= { hmWanMbus4B 59 }

hmWanMbus4BVIF1B		OBJECT-TYPE
			SYNTAX	INTEGER
			MAX-ACCESS	read-only
			STATUS	current
			::= { hmWanMbus4B 60 }

hmWanMbus4BValue1B		OBJECT-TYPE
			SYNTAX	INTEGER
			MAX-ACCESS	read-only
			STATUS	current
			::= { hmWanMbus4B 61 }

hmWanMbus4BVIF1C		OBJECT-TYPE
			SYNTAX	INTEGER
			MAX-ACCESS	read-only
			STATUS	current
			::= { hmWanMbus4B 62 }

hmWanMbus4BValue1C		OBJECT-TYPE
			SYNTAX	INTEGER
			MAX-ACCESS	read-only
			STATUS	current
			::= { hmWanMbus4B 63 }

hmWanMbus4BVIF1D		OBJECT-TYPE
			SYNTAX	INTEGER
			MAX-ACCESS	read-only
			STATUS	current
			::= { hmWanMbus4B 64 }

hmWanMbus4BValue1D		OBJECT-TYPE
			SYNTAX	INTEGER
			MAX-ACCESS	read-only
			STATUS	current
			::= { hmWanMbus4B 65 }

hmWanMbus4BVIF1E		OBJECT-TYPE
			SYNTAX	INTEGER
			MAX-ACCESS	read-only
			STATUS	current
			::= { hmWanMbus4B 66 }

hmWanMbus4BValue1E		OBJECT-TYPE
			SYNTAX	INTEGER
			MAX-ACCESS	read-only
			STATUS	current
			::= { hmWanMbus4B 67 }

hmWanMbus4BVIF1F		OBJECT-TYPE
			SYNTAX	INTEGER
			MAX-ACCESS	read-only
			STATUS	current
			::= { hmWanMbus4B 68 }

hmWanMbus4BValue1F		OBJECT-TYPE
			SYNTAX	INTEGER
			MAX-ACCESS	read-only
			STATUS	current
			::= { hmWanMbus4B 69 }

hmWanMbus4BVIF20		OBJECT-TYPE
			SYNTAX	INTEGER
			MAX-ACCESS	read-only
			STATUS	current
			::= { hmWanMbus4B 70 }

hmWanMbus4BValue20		OBJECT-TYPE
			SYNTAX	INTEGER
			MAX-ACCESS	read-only
			STATUS	current
			::= { hmWanMbus4B 71 }

hmWanMbus4BVIF21		OBJECT-TYPE
			SYNTAX	INTEGER
			MAX-ACCESS	read-only
			STATUS	current
			::= { hmWanMbus4B 72 }

hmWanMbus4BValue21		OBJECT-TYPE
			SYNTAX	INTEGER
			MAX-ACCESS	read-only
			STATUS	current
			::= { hmWanMbus4B 73 }

hmWanMbus4BVIF22		OBJECT-TYPE
			SYNTAX	INTEGER
			MAX-ACCESS	read-only
			STATUS	current
			::= { hmWanMbus4B 74 }

hmWanMbus4BValue22		OBJECT-TYPE
			SYNTAX	INTEGER
			MAX-ACCESS	read-only
			STATUS	current
			::= { hmWanMbus4B 75 }

hmWanMbus4BVIF23		OBJECT-TYPE
			SYNTAX	INTEGER
			MAX-ACCESS	read-only
			STATUS	current
			::= { hmWanMbus4B 76 }

hmWanMbus4BValue23		OBJECT-TYPE
			SYNTAX	INTEGER
			MAX-ACCESS	read-only
			STATUS	current
			::= { hmWanMbus4B 77 }

hmWanMbus4BVIF24		OBJECT-TYPE
			SYNTAX	INTEGER
			MAX-ACCESS	read-only
			STATUS	current
			::= { hmWanMbus4B 78 }

hmWanMbus4BValue24		OBJECT-TYPE
			SYNTAX	INTEGER
			MAX-ACCESS	read-only
			STATUS	current
			::= { hmWanMbus4B 79 }

hmWanMbus4BVIF25		OBJECT-TYPE
			SYNTAX	INTEGER
			MAX-ACCESS	read-only
			STATUS	current
			::= { hmWanMbus4B 80 }

hmWanMbus4BValue25		OBJECT-TYPE
			SYNTAX	INTEGER
			MAX-ACCESS	read-only
			STATUS	current
			::= { hmWanMbus4B 81 }

hmWanMbus4BVIF26		OBJECT-TYPE
			SYNTAX	INTEGER
			MAX-ACCESS	read-only
			STATUS	current
			::= { hmWanMbus4B 82 }

hmWanMbus4BValue26		OBJECT-TYPE
			SYNTAX	INTEGER
			MAX-ACCESS	read-only
			STATUS	current
			::= { hmWanMbus4B 83 }

hmWanMbus4BVIF27		OBJECT-TYPE
			SYNTAX	INTEGER
			MAX-ACCESS	read-only
			STATUS	current
			::= { hmWanMbus4B 84 }

hmWanMbus4BValue27		OBJECT-TYPE
			SYNTAX	INTEGER
			MAX-ACCESS	read-only
			STATUS	current
			::= { hmWanMbus4B 85 }

hmWanMbus4BVIF28		OBJECT-TYPE
			SYNTAX	INTEGER
			MAX-ACCESS	read-only
			STATUS	current
			::= { hmWanMbus4B 86 }

hmWanMbus4BValue28		OBJECT-TYPE
			SYNTAX	INTEGER
			MAX-ACCESS	read-only
			STATUS	current
			::= { hmWanMbus4B 87 }

hmWanMbus4BVIF29		OBJECT-TYPE
			SYNTAX	INTEGER
			MAX-ACCESS	read-only
			STATUS	current
			::= { hmWanMbus4B 88 }

hmWanMbus4BValue29		OBJECT-TYPE
			SYNTAX	INTEGER
			MAX-ACCESS	read-only
			STATUS	current
			::= { hmWanMbus4B 89 }

hmWanMbus4BVIF2A		OBJECT-TYPE
			SYNTAX	INTEGER
			MAX-ACCESS	read-only
			STATUS	current
			::= { hmWanMbus4B 90 }

hmWanMbus4BValue2A		OBJECT-TYPE
			SYNTAX	INTEGER
			MAX-ACCESS	read-only
			STATUS	current
			::= { hmWanMbus4B 91 }

hmWanMbus4BVIF2B		OBJECT-TYPE
			SYNTAX	INTEGER
			MAX-ACCESS	read-only
			STATUS	current
			::= { hmWanMbus4B 92 }

hmWanMbus4BValue2B		OBJECT-TYPE
			SYNTAX	INTEGER
			MAX-ACCESS	read-only
			STATUS	current
			::= { hmWanMbus4B 93 }

hmWanMbus4BVIF2C		OBJECT-TYPE
			SYNTAX	INTEGER
			MAX-ACCESS	read-only
			STATUS	current
			::= { hmWanMbus4B 94 }

hmWanMbus4BValue2C		OBJECT-TYPE
			SYNTAX	INTEGER
			MAX-ACCESS	read-only
			STATUS	current
			::= { hmWanMbus4B 95 }

hmWanMbus4BVIF2D		OBJECT-TYPE
			SYNTAX	INTEGER
			MAX-ACCESS	read-only
			STATUS	current
			::= { hmWanMbus4B 96 }

hmWanMbus4BValue2D		OBJECT-TYPE
			SYNTAX	INTEGER
			MAX-ACCESS	read-only
			STATUS	current
			::= { hmWanMbus4B 97 }

hmWanMbus4BVIF2E		OBJECT-TYPE
			SYNTAX	INTEGER
			MAX-ACCESS	read-only
			STATUS	current
			::= { hmWanMbus4B 98 }

hmWanMbus4BValue2E		OBJECT-TYPE
			SYNTAX	INTEGER
			MAX-ACCESS	read-only
			STATUS	current
			::= { hmWanMbus4B 99 }

hmWanMbus4BVIF2F		OBJECT-TYPE
			SYNTAX	INTEGER
			MAX-ACCESS	read-only
			STATUS	current
			::= { hmWanMbus4B 100 }

hmWanMbus4BValue2F		OBJECT-TYPE
			SYNTAX	INTEGER
			MAX-ACCESS	read-only
			STATUS	current
			::= { hmWanMbus4B 101 }

hmWanMbus4C			OBJECT IDENTIFIER ::= { hmWanMbus 76 }

hmWanMbus4CIdNumber		OBJECT-TYPE
			SYNTAX	Gauge32
			MAX-ACCESS	read-only
			STATUS	current
			::= { hmWanMbus4C 1 }

hmWanMbus4CManufacturer	OBJECT-TYPE
			SYNTAX	Gauge32
			MAX-ACCESS	read-only
			STATUS	current
			::= { hmWanMbus4C 2 }

hmWanMbus4CVersion		OBJECT-TYPE
			SYNTAX	Gauge32
			MAX-ACCESS	read-only
			STATUS	current
			::= { hmWanMbus4C 3 }

hmWanMbus4CMedium		OBJECT-TYPE
			SYNTAX	Gauge32
			MAX-ACCESS	read-only
			STATUS	current
			::= { hmWanMbus4C 4 }

hmWanMbus4CStatus		OBJECT-TYPE
			SYNTAX	Gauge32
			MAX-ACCESS	read-only
			STATUS	current
			::= { hmWanMbus4C 5 }

hmWanMbus4CVIF00		OBJECT-TYPE
			SYNTAX	INTEGER
			MAX-ACCESS	read-only
			STATUS	current
			::= { hmWanMbus4C 6 }

hmWanMbus4CValue00		OBJECT-TYPE
			SYNTAX	INTEGER
			MAX-ACCESS	read-only
			STATUS	current
			::= { hmWanMbus4C 7 }

hmWanMbus4CVIF01		OBJECT-TYPE
			SYNTAX	INTEGER
			MAX-ACCESS	read-only
			STATUS	current
			::= { hmWanMbus4C 8 }

hmWanMbus4CValue01		OBJECT-TYPE
			SYNTAX	INTEGER
			MAX-ACCESS	read-only
			STATUS	current
			::= { hmWanMbus4C 9 }

hmWanMbus4CVIF02		OBJECT-TYPE
			SYNTAX	INTEGER
			MAX-ACCESS	read-only
			STATUS	current
			::= { hmWanMbus4C 10 }

hmWanMbus4CValue02		OBJECT-TYPE
			SYNTAX	INTEGER
			MAX-ACCESS	read-only
			STATUS	current
			::= { hmWanMbus4C 11 }

hmWanMbus4CVIF03		OBJECT-TYPE
			SYNTAX	INTEGER
			MAX-ACCESS	read-only
			STATUS	current
			::= { hmWanMbus4C 12 }

hmWanMbus4CValue03		OBJECT-TYPE
			SYNTAX	INTEGER
			MAX-ACCESS	read-only
			STATUS	current
			::= { hmWanMbus4C 13 }

hmWanMbus4CVIF04		OBJECT-TYPE
			SYNTAX	INTEGER
			MAX-ACCESS	read-only
			STATUS	current
			::= { hmWanMbus4C 14 }

hmWanMbus4CValue04		OBJECT-TYPE
			SYNTAX	INTEGER
			MAX-ACCESS	read-only
			STATUS	current
			::= { hmWanMbus4C 15 }

hmWanMbus4CVIF05		OBJECT-TYPE
			SYNTAX	INTEGER
			MAX-ACCESS	read-only
			STATUS	current
			::= { hmWanMbus4C 16 }

hmWanMbus4CValue05		OBJECT-TYPE
			SYNTAX	INTEGER
			MAX-ACCESS	read-only
			STATUS	current
			::= { hmWanMbus4C 17 }

hmWanMbus4CVIF06		OBJECT-TYPE
			SYNTAX	INTEGER
			MAX-ACCESS	read-only
			STATUS	current
			::= { hmWanMbus4C 18 }

hmWanMbus4CValue06		OBJECT-TYPE
			SYNTAX	INTEGER
			MAX-ACCESS	read-only
			STATUS	current
			::= { hmWanMbus4C 19 }

hmWanMbus4CVIF07		OBJECT-TYPE
			SYNTAX	INTEGER
			MAX-ACCESS	read-only
			STATUS	current
			::= { hmWanMbus4C 20 }

hmWanMbus4CValue07		OBJECT-TYPE
			SYNTAX	INTEGER
			MAX-ACCESS	read-only
			STATUS	current
			::= { hmWanMbus4C 21 }

hmWanMbus4CVIF08		OBJECT-TYPE
			SYNTAX	INTEGER
			MAX-ACCESS	read-only
			STATUS	current
			::= { hmWanMbus4C 22 }

hmWanMbus4CValue08		OBJECT-TYPE
			SYNTAX	INTEGER
			MAX-ACCESS	read-only
			STATUS	current
			::= { hmWanMbus4C 23 }

hmWanMbus4CVIF09		OBJECT-TYPE
			SYNTAX	INTEGER
			MAX-ACCESS	read-only
			STATUS	current
			::= { hmWanMbus4C 24 }

hmWanMbus4CValue09		OBJECT-TYPE
			SYNTAX	INTEGER
			MAX-ACCESS	read-only
			STATUS	current
			::= { hmWanMbus4C 25 }

hmWanMbus4CVIF0A		OBJECT-TYPE
			SYNTAX	INTEGER
			MAX-ACCESS	read-only
			STATUS	current
			::= { hmWanMbus4C 26 }

hmWanMbus4CValue0A		OBJECT-TYPE
			SYNTAX	INTEGER
			MAX-ACCESS	read-only
			STATUS	current
			::= { hmWanMbus4C 27 }

hmWanMbus4CVIF0B		OBJECT-TYPE
			SYNTAX	INTEGER
			MAX-ACCESS	read-only
			STATUS	current
			::= { hmWanMbus4C 28 }

hmWanMbus4CValue0B		OBJECT-TYPE
			SYNTAX	INTEGER
			MAX-ACCESS	read-only
			STATUS	current
			::= { hmWanMbus4C 29 }

hmWanMbus4CVIF0C		OBJECT-TYPE
			SYNTAX	INTEGER
			MAX-ACCESS	read-only
			STATUS	current
			::= { hmWanMbus4C 30 }

hmWanMbus4CValue0C		OBJECT-TYPE
			SYNTAX	INTEGER
			MAX-ACCESS	read-only
			STATUS	current
			::= { hmWanMbus4C 31 }

hmWanMbus4CVIF0D		OBJECT-TYPE
			SYNTAX	INTEGER
			MAX-ACCESS	read-only
			STATUS	current
			::= { hmWanMbus4C 32 }

hmWanMbus4CValue0D		OBJECT-TYPE
			SYNTAX	INTEGER
			MAX-ACCESS	read-only
			STATUS	current
			::= { hmWanMbus4C 33 }

hmWanMbus4CVIF0E		OBJECT-TYPE
			SYNTAX	INTEGER
			MAX-ACCESS	read-only
			STATUS	current
			::= { hmWanMbus4C 34 }

hmWanMbus4CValue0E		OBJECT-TYPE
			SYNTAX	INTEGER
			MAX-ACCESS	read-only
			STATUS	current
			::= { hmWanMbus4C 35 }

hmWanMbus4CVIF0F		OBJECT-TYPE
			SYNTAX	INTEGER
			MAX-ACCESS	read-only
			STATUS	current
			::= { hmWanMbus4C 36 }

hmWanMbus4CValue0F		OBJECT-TYPE
			SYNTAX	INTEGER
			MAX-ACCESS	read-only
			STATUS	current
			::= { hmWanMbus4C 37 }

hmWanMbus4CVIF10		OBJECT-TYPE
			SYNTAX	INTEGER
			MAX-ACCESS	read-only
			STATUS	current
			::= { hmWanMbus4C 38 }

hmWanMbus4CValue10		OBJECT-TYPE
			SYNTAX	INTEGER
			MAX-ACCESS	read-only
			STATUS	current
			::= { hmWanMbus4C 39 }

hmWanMbus4CVIF11		OBJECT-TYPE
			SYNTAX	INTEGER
			MAX-ACCESS	read-only
			STATUS	current
			::= { hmWanMbus4C 40 }

hmWanMbus4CValue11		OBJECT-TYPE
			SYNTAX	INTEGER
			MAX-ACCESS	read-only
			STATUS	current
			::= { hmWanMbus4C 41 }

hmWanMbus4CVIF12		OBJECT-TYPE
			SYNTAX	INTEGER
			MAX-ACCESS	read-only
			STATUS	current
			::= { hmWanMbus4C 42 }

hmWanMbus4CValue12		OBJECT-TYPE
			SYNTAX	INTEGER
			MAX-ACCESS	read-only
			STATUS	current
			::= { hmWanMbus4C 43 }

hmWanMbus4CVIF13		OBJECT-TYPE
			SYNTAX	INTEGER
			MAX-ACCESS	read-only
			STATUS	current
			::= { hmWanMbus4C 44 }

hmWanMbus4CValue13		OBJECT-TYPE
			SYNTAX	INTEGER
			MAX-ACCESS	read-only
			STATUS	current
			::= { hmWanMbus4C 45 }

hmWanMbus4CVIF14		OBJECT-TYPE
			SYNTAX	INTEGER
			MAX-ACCESS	read-only
			STATUS	current
			::= { hmWanMbus4C 46 }

hmWanMbus4CValue14		OBJECT-TYPE
			SYNTAX	INTEGER
			MAX-ACCESS	read-only
			STATUS	current
			::= { hmWanMbus4C 47 }

hmWanMbus4CVIF15		OBJECT-TYPE
			SYNTAX	INTEGER
			MAX-ACCESS	read-only
			STATUS	current
			::= { hmWanMbus4C 48 }

hmWanMbus4CValue15		OBJECT-TYPE
			SYNTAX	INTEGER
			MAX-ACCESS	read-only
			STATUS	current
			::= { hmWanMbus4C 49 }

hmWanMbus4CVIF16		OBJECT-TYPE
			SYNTAX	INTEGER
			MAX-ACCESS	read-only
			STATUS	current
			::= { hmWanMbus4C 50 }

hmWanMbus4CValue16		OBJECT-TYPE
			SYNTAX	INTEGER
			MAX-ACCESS	read-only
			STATUS	current
			::= { hmWanMbus4C 51 }

hmWanMbus4CVIF17		OBJECT-TYPE
			SYNTAX	INTEGER
			MAX-ACCESS	read-only
			STATUS	current
			::= { hmWanMbus4C 52 }

hmWanMbus4CValue17		OBJECT-TYPE
			SYNTAX	INTEGER
			MAX-ACCESS	read-only
			STATUS	current
			::= { hmWanMbus4C 53 }

hmWanMbus4CVIF18		OBJECT-TYPE
			SYNTAX	INTEGER
			MAX-ACCESS	read-only
			STATUS	current
			::= { hmWanMbus4C 54 }

hmWanMbus4CValue18		OBJECT-TYPE
			SYNTAX	INTEGER
			MAX-ACCESS	read-only
			STATUS	current
			::= { hmWanMbus4C 55 }

hmWanMbus4CVIF19		OBJECT-TYPE
			SYNTAX	INTEGER
			MAX-ACCESS	read-only
			STATUS	current
			::= { hmWanMbus4C 56 }

hmWanMbus4CValue19		OBJECT-TYPE
			SYNTAX	INTEGER
			MAX-ACCESS	read-only
			STATUS	current
			::= { hmWanMbus4C 57 }

hmWanMbus4CVIF1A		OBJECT-TYPE
			SYNTAX	INTEGER
			MAX-ACCESS	read-only
			STATUS	current
			::= { hmWanMbus4C 58 }

hmWanMbus4CValue1A		OBJECT-TYPE
			SYNTAX	INTEGER
			MAX-ACCESS	read-only
			STATUS	current
			::= { hmWanMbus4C 59 }

hmWanMbus4CVIF1B		OBJECT-TYPE
			SYNTAX	INTEGER
			MAX-ACCESS	read-only
			STATUS	current
			::= { hmWanMbus4C 60 }

hmWanMbus4CValue1B		OBJECT-TYPE
			SYNTAX	INTEGER
			MAX-ACCESS	read-only
			STATUS	current
			::= { hmWanMbus4C 61 }

hmWanMbus4CVIF1C		OBJECT-TYPE
			SYNTAX	INTEGER
			MAX-ACCESS	read-only
			STATUS	current
			::= { hmWanMbus4C 62 }

hmWanMbus4CValue1C		OBJECT-TYPE
			SYNTAX	INTEGER
			MAX-ACCESS	read-only
			STATUS	current
			::= { hmWanMbus4C 63 }

hmWanMbus4CVIF1D		OBJECT-TYPE
			SYNTAX	INTEGER
			MAX-ACCESS	read-only
			STATUS	current
			::= { hmWanMbus4C 64 }

hmWanMbus4CValue1D		OBJECT-TYPE
			SYNTAX	INTEGER
			MAX-ACCESS	read-only
			STATUS	current
			::= { hmWanMbus4C 65 }

hmWanMbus4CVIF1E		OBJECT-TYPE
			SYNTAX	INTEGER
			MAX-ACCESS	read-only
			STATUS	current
			::= { hmWanMbus4C 66 }

hmWanMbus4CValue1E		OBJECT-TYPE
			SYNTAX	INTEGER
			MAX-ACCESS	read-only
			STATUS	current
			::= { hmWanMbus4C 67 }

hmWanMbus4CVIF1F		OBJECT-TYPE
			SYNTAX	INTEGER
			MAX-ACCESS	read-only
			STATUS	current
			::= { hmWanMbus4C 68 }

hmWanMbus4CValue1F		OBJECT-TYPE
			SYNTAX	INTEGER
			MAX-ACCESS	read-only
			STATUS	current
			::= { hmWanMbus4C 69 }

hmWanMbus4CVIF20		OBJECT-TYPE
			SYNTAX	INTEGER
			MAX-ACCESS	read-only
			STATUS	current
			::= { hmWanMbus4C 70 }

hmWanMbus4CValue20		OBJECT-TYPE
			SYNTAX	INTEGER
			MAX-ACCESS	read-only
			STATUS	current
			::= { hmWanMbus4C 71 }

hmWanMbus4CVIF21		OBJECT-TYPE
			SYNTAX	INTEGER
			MAX-ACCESS	read-only
			STATUS	current
			::= { hmWanMbus4C 72 }

hmWanMbus4CValue21		OBJECT-TYPE
			SYNTAX	INTEGER
			MAX-ACCESS	read-only
			STATUS	current
			::= { hmWanMbus4C 73 }

hmWanMbus4CVIF22		OBJECT-TYPE
			SYNTAX	INTEGER
			MAX-ACCESS	read-only
			STATUS	current
			::= { hmWanMbus4C 74 }

hmWanMbus4CValue22		OBJECT-TYPE
			SYNTAX	INTEGER
			MAX-ACCESS	read-only
			STATUS	current
			::= { hmWanMbus4C 75 }

hmWanMbus4CVIF23		OBJECT-TYPE
			SYNTAX	INTEGER
			MAX-ACCESS	read-only
			STATUS	current
			::= { hmWanMbus4C 76 }

hmWanMbus4CValue23		OBJECT-TYPE
			SYNTAX	INTEGER
			MAX-ACCESS	read-only
			STATUS	current
			::= { hmWanMbus4C 77 }

hmWanMbus4CVIF24		OBJECT-TYPE
			SYNTAX	INTEGER
			MAX-ACCESS	read-only
			STATUS	current
			::= { hmWanMbus4C 78 }

hmWanMbus4CValue24		OBJECT-TYPE
			SYNTAX	INTEGER
			MAX-ACCESS	read-only
			STATUS	current
			::= { hmWanMbus4C 79 }

hmWanMbus4CVIF25		OBJECT-TYPE
			SYNTAX	INTEGER
			MAX-ACCESS	read-only
			STATUS	current
			::= { hmWanMbus4C 80 }

hmWanMbus4CValue25		OBJECT-TYPE
			SYNTAX	INTEGER
			MAX-ACCESS	read-only
			STATUS	current
			::= { hmWanMbus4C 81 }

hmWanMbus4CVIF26		OBJECT-TYPE
			SYNTAX	INTEGER
			MAX-ACCESS	read-only
			STATUS	current
			::= { hmWanMbus4C 82 }

hmWanMbus4CValue26		OBJECT-TYPE
			SYNTAX	INTEGER
			MAX-ACCESS	read-only
			STATUS	current
			::= { hmWanMbus4C 83 }

hmWanMbus4CVIF27		OBJECT-TYPE
			SYNTAX	INTEGER
			MAX-ACCESS	read-only
			STATUS	current
			::= { hmWanMbus4C 84 }

hmWanMbus4CValue27		OBJECT-TYPE
			SYNTAX	INTEGER
			MAX-ACCESS	read-only
			STATUS	current
			::= { hmWanMbus4C 85 }

hmWanMbus4CVIF28		OBJECT-TYPE
			SYNTAX	INTEGER
			MAX-ACCESS	read-only
			STATUS	current
			::= { hmWanMbus4C 86 }

hmWanMbus4CValue28		OBJECT-TYPE
			SYNTAX	INTEGER
			MAX-ACCESS	read-only
			STATUS	current
			::= { hmWanMbus4C 87 }

hmWanMbus4CVIF29		OBJECT-TYPE
			SYNTAX	INTEGER
			MAX-ACCESS	read-only
			STATUS	current
			::= { hmWanMbus4C 88 }

hmWanMbus4CValue29		OBJECT-TYPE
			SYNTAX	INTEGER
			MAX-ACCESS	read-only
			STATUS	current
			::= { hmWanMbus4C 89 }

hmWanMbus4CVIF2A		OBJECT-TYPE
			SYNTAX	INTEGER
			MAX-ACCESS	read-only
			STATUS	current
			::= { hmWanMbus4C 90 }

hmWanMbus4CValue2A		OBJECT-TYPE
			SYNTAX	INTEGER
			MAX-ACCESS	read-only
			STATUS	current
			::= { hmWanMbus4C 91 }

hmWanMbus4CVIF2B		OBJECT-TYPE
			SYNTAX	INTEGER
			MAX-ACCESS	read-only
			STATUS	current
			::= { hmWanMbus4C 92 }

hmWanMbus4CValue2B		OBJECT-TYPE
			SYNTAX	INTEGER
			MAX-ACCESS	read-only
			STATUS	current
			::= { hmWanMbus4C 93 }

hmWanMbus4CVIF2C		OBJECT-TYPE
			SYNTAX	INTEGER
			MAX-ACCESS	read-only
			STATUS	current
			::= { hmWanMbus4C 94 }

hmWanMbus4CValue2C		OBJECT-TYPE
			SYNTAX	INTEGER
			MAX-ACCESS	read-only
			STATUS	current
			::= { hmWanMbus4C 95 }

hmWanMbus4CVIF2D		OBJECT-TYPE
			SYNTAX	INTEGER
			MAX-ACCESS	read-only
			STATUS	current
			::= { hmWanMbus4C 96 }

hmWanMbus4CValue2D		OBJECT-TYPE
			SYNTAX	INTEGER
			MAX-ACCESS	read-only
			STATUS	current
			::= { hmWanMbus4C 97 }

hmWanMbus4CVIF2E		OBJECT-TYPE
			SYNTAX	INTEGER
			MAX-ACCESS	read-only
			STATUS	current
			::= { hmWanMbus4C 98 }

hmWanMbus4CValue2E		OBJECT-TYPE
			SYNTAX	INTEGER
			MAX-ACCESS	read-only
			STATUS	current
			::= { hmWanMbus4C 99 }

hmWanMbus4CVIF2F		OBJECT-TYPE
			SYNTAX	INTEGER
			MAX-ACCESS	read-only
			STATUS	current
			::= { hmWanMbus4C 100 }

hmWanMbus4CValue2F		OBJECT-TYPE
			SYNTAX	INTEGER
			MAX-ACCESS	read-only
			STATUS	current
			::= { hmWanMbus4C 101 }

hmWanMbus4D			OBJECT IDENTIFIER ::= { hmWanMbus 77 }

hmWanMbus4DIdNumber		OBJECT-TYPE
			SYNTAX	Gauge32
			MAX-ACCESS	read-only
			STATUS	current
			::= { hmWanMbus4D 1 }

hmWanMbus4DManufacturer	OBJECT-TYPE
			SYNTAX	Gauge32
			MAX-ACCESS	read-only
			STATUS	current
			::= { hmWanMbus4D 2 }

hmWanMbus4DVersion		OBJECT-TYPE
			SYNTAX	Gauge32
			MAX-ACCESS	read-only
			STATUS	current
			::= { hmWanMbus4D 3 }

hmWanMbus4DMedium		OBJECT-TYPE
			SYNTAX	Gauge32
			MAX-ACCESS	read-only
			STATUS	current
			::= { hmWanMbus4D 4 }

hmWanMbus4DStatus		OBJECT-TYPE
			SYNTAX	Gauge32
			MAX-ACCESS	read-only
			STATUS	current
			::= { hmWanMbus4D 5 }

hmWanMbus4DVIF00		OBJECT-TYPE
			SYNTAX	INTEGER
			MAX-ACCESS	read-only
			STATUS	current
			::= { hmWanMbus4D 6 }

hmWanMbus4DValue00		OBJECT-TYPE
			SYNTAX	INTEGER
			MAX-ACCESS	read-only
			STATUS	current
			::= { hmWanMbus4D 7 }

hmWanMbus4DVIF01		OBJECT-TYPE
			SYNTAX	INTEGER
			MAX-ACCESS	read-only
			STATUS	current
			::= { hmWanMbus4D 8 }

hmWanMbus4DValue01		OBJECT-TYPE
			SYNTAX	INTEGER
			MAX-ACCESS	read-only
			STATUS	current
			::= { hmWanMbus4D 9 }

hmWanMbus4DVIF02		OBJECT-TYPE
			SYNTAX	INTEGER
			MAX-ACCESS	read-only
			STATUS	current
			::= { hmWanMbus4D 10 }

hmWanMbus4DValue02		OBJECT-TYPE
			SYNTAX	INTEGER
			MAX-ACCESS	read-only
			STATUS	current
			::= { hmWanMbus4D 11 }

hmWanMbus4DVIF03		OBJECT-TYPE
			SYNTAX	INTEGER
			MAX-ACCESS	read-only
			STATUS	current
			::= { hmWanMbus4D 12 }

hmWanMbus4DValue03		OBJECT-TYPE
			SYNTAX	INTEGER
			MAX-ACCESS	read-only
			STATUS	current
			::= { hmWanMbus4D 13 }

hmWanMbus4DVIF04		OBJECT-TYPE
			SYNTAX	INTEGER
			MAX-ACCESS	read-only
			STATUS	current
			::= { hmWanMbus4D 14 }

hmWanMbus4DValue04		OBJECT-TYPE
			SYNTAX	INTEGER
			MAX-ACCESS	read-only
			STATUS	current
			::= { hmWanMbus4D 15 }

hmWanMbus4DVIF05		OBJECT-TYPE
			SYNTAX	INTEGER
			MAX-ACCESS	read-only
			STATUS	current
			::= { hmWanMbus4D 16 }

hmWanMbus4DValue05		OBJECT-TYPE
			SYNTAX	INTEGER
			MAX-ACCESS	read-only
			STATUS	current
			::= { hmWanMbus4D 17 }

hmWanMbus4DVIF06		OBJECT-TYPE
			SYNTAX	INTEGER
			MAX-ACCESS	read-only
			STATUS	current
			::= { hmWanMbus4D 18 }

hmWanMbus4DValue06		OBJECT-TYPE
			SYNTAX	INTEGER
			MAX-ACCESS	read-only
			STATUS	current
			::= { hmWanMbus4D 19 }

hmWanMbus4DVIF07		OBJECT-TYPE
			SYNTAX	INTEGER
			MAX-ACCESS	read-only
			STATUS	current
			::= { hmWanMbus4D 20 }

hmWanMbus4DValue07		OBJECT-TYPE
			SYNTAX	INTEGER
			MAX-ACCESS	read-only
			STATUS	current
			::= { hmWanMbus4D 21 }

hmWanMbus4DVIF08		OBJECT-TYPE
			SYNTAX	INTEGER
			MAX-ACCESS	read-only
			STATUS	current
			::= { hmWanMbus4D 22 }

hmWanMbus4DValue08		OBJECT-TYPE
			SYNTAX	INTEGER
			MAX-ACCESS	read-only
			STATUS	current
			::= { hmWanMbus4D 23 }

hmWanMbus4DVIF09		OBJECT-TYPE
			SYNTAX	INTEGER
			MAX-ACCESS	read-only
			STATUS	current
			::= { hmWanMbus4D 24 }

hmWanMbus4DValue09		OBJECT-TYPE
			SYNTAX	INTEGER
			MAX-ACCESS	read-only
			STATUS	current
			::= { hmWanMbus4D 25 }

hmWanMbus4DVIF0A		OBJECT-TYPE
			SYNTAX	INTEGER
			MAX-ACCESS	read-only
			STATUS	current
			::= { hmWanMbus4D 26 }

hmWanMbus4DValue0A		OBJECT-TYPE
			SYNTAX	INTEGER
			MAX-ACCESS	read-only
			STATUS	current
			::= { hmWanMbus4D 27 }

hmWanMbus4DVIF0B		OBJECT-TYPE
			SYNTAX	INTEGER
			MAX-ACCESS	read-only
			STATUS	current
			::= { hmWanMbus4D 28 }

hmWanMbus4DValue0B		OBJECT-TYPE
			SYNTAX	INTEGER
			MAX-ACCESS	read-only
			STATUS	current
			::= { hmWanMbus4D 29 }

hmWanMbus4DVIF0C		OBJECT-TYPE
			SYNTAX	INTEGER
			MAX-ACCESS	read-only
			STATUS	current
			::= { hmWanMbus4D 30 }

hmWanMbus4DValue0C		OBJECT-TYPE
			SYNTAX	INTEGER
			MAX-ACCESS	read-only
			STATUS	current
			::= { hmWanMbus4D 31 }

hmWanMbus4DVIF0D		OBJECT-TYPE
			SYNTAX	INTEGER
			MAX-ACCESS	read-only
			STATUS	current
			::= { hmWanMbus4D 32 }

hmWanMbus4DValue0D		OBJECT-TYPE
			SYNTAX	INTEGER
			MAX-ACCESS	read-only
			STATUS	current
			::= { hmWanMbus4D 33 }

hmWanMbus4DVIF0E		OBJECT-TYPE
			SYNTAX	INTEGER
			MAX-ACCESS	read-only
			STATUS	current
			::= { hmWanMbus4D 34 }

hmWanMbus4DValue0E		OBJECT-TYPE
			SYNTAX	INTEGER
			MAX-ACCESS	read-only
			STATUS	current
			::= { hmWanMbus4D 35 }

hmWanMbus4DVIF0F		OBJECT-TYPE
			SYNTAX	INTEGER
			MAX-ACCESS	read-only
			STATUS	current
			::= { hmWanMbus4D 36 }

hmWanMbus4DValue0F		OBJECT-TYPE
			SYNTAX	INTEGER
			MAX-ACCESS	read-only
			STATUS	current
			::= { hmWanMbus4D 37 }

hmWanMbus4DVIF10		OBJECT-TYPE
			SYNTAX	INTEGER
			MAX-ACCESS	read-only
			STATUS	current
			::= { hmWanMbus4D 38 }

hmWanMbus4DValue10		OBJECT-TYPE
			SYNTAX	INTEGER
			MAX-ACCESS	read-only
			STATUS	current
			::= { hmWanMbus4D 39 }

hmWanMbus4DVIF11		OBJECT-TYPE
			SYNTAX	INTEGER
			MAX-ACCESS	read-only
			STATUS	current
			::= { hmWanMbus4D 40 }

hmWanMbus4DValue11		OBJECT-TYPE
			SYNTAX	INTEGER
			MAX-ACCESS	read-only
			STATUS	current
			::= { hmWanMbus4D 41 }

hmWanMbus4DVIF12		OBJECT-TYPE
			SYNTAX	INTEGER
			MAX-ACCESS	read-only
			STATUS	current
			::= { hmWanMbus4D 42 }

hmWanMbus4DValue12		OBJECT-TYPE
			SYNTAX	INTEGER
			MAX-ACCESS	read-only
			STATUS	current
			::= { hmWanMbus4D 43 }

hmWanMbus4DVIF13		OBJECT-TYPE
			SYNTAX	INTEGER
			MAX-ACCESS	read-only
			STATUS	current
			::= { hmWanMbus4D 44 }

hmWanMbus4DValue13		OBJECT-TYPE
			SYNTAX	INTEGER
			MAX-ACCESS	read-only
			STATUS	current
			::= { hmWanMbus4D 45 }

hmWanMbus4DVIF14		OBJECT-TYPE
			SYNTAX	INTEGER
			MAX-ACCESS	read-only
			STATUS	current
			::= { hmWanMbus4D 46 }

hmWanMbus4DValue14		OBJECT-TYPE
			SYNTAX	INTEGER
			MAX-ACCESS	read-only
			STATUS	current
			::= { hmWanMbus4D 47 }

hmWanMbus4DVIF15		OBJECT-TYPE
			SYNTAX	INTEGER
			MAX-ACCESS	read-only
			STATUS	current
			::= { hmWanMbus4D 48 }

hmWanMbus4DValue15		OBJECT-TYPE
			SYNTAX	INTEGER
			MAX-ACCESS	read-only
			STATUS	current
			::= { hmWanMbus4D 49 }

hmWanMbus4DVIF16		OBJECT-TYPE
			SYNTAX	INTEGER
			MAX-ACCESS	read-only
			STATUS	current
			::= { hmWanMbus4D 50 }

hmWanMbus4DValue16		OBJECT-TYPE
			SYNTAX	INTEGER
			MAX-ACCESS	read-only
			STATUS	current
			::= { hmWanMbus4D 51 }

hmWanMbus4DVIF17		OBJECT-TYPE
			SYNTAX	INTEGER
			MAX-ACCESS	read-only
			STATUS	current
			::= { hmWanMbus4D 52 }

hmWanMbus4DValue17		OBJECT-TYPE
			SYNTAX	INTEGER
			MAX-ACCESS	read-only
			STATUS	current
			::= { hmWanMbus4D 53 }

hmWanMbus4DVIF18		OBJECT-TYPE
			SYNTAX	INTEGER
			MAX-ACCESS	read-only
			STATUS	current
			::= { hmWanMbus4D 54 }

hmWanMbus4DValue18		OBJECT-TYPE
			SYNTAX	INTEGER
			MAX-ACCESS	read-only
			STATUS	current
			::= { hmWanMbus4D 55 }

hmWanMbus4DVIF19		OBJECT-TYPE
			SYNTAX	INTEGER
			MAX-ACCESS	read-only
			STATUS	current
			::= { hmWanMbus4D 56 }

hmWanMbus4DValue19		OBJECT-TYPE
			SYNTAX	INTEGER
			MAX-ACCESS	read-only
			STATUS	current
			::= { hmWanMbus4D 57 }

hmWanMbus4DVIF1A		OBJECT-TYPE
			SYNTAX	INTEGER
			MAX-ACCESS	read-only
			STATUS	current
			::= { hmWanMbus4D 58 }

hmWanMbus4DValue1A		OBJECT-TYPE
			SYNTAX	INTEGER
			MAX-ACCESS	read-only
			STATUS	current
			::= { hmWanMbus4D 59 }

hmWanMbus4DVIF1B		OBJECT-TYPE
			SYNTAX	INTEGER
			MAX-ACCESS	read-only
			STATUS	current
			::= { hmWanMbus4D 60 }

hmWanMbus4DValue1B		OBJECT-TYPE
			SYNTAX	INTEGER
			MAX-ACCESS	read-only
			STATUS	current
			::= { hmWanMbus4D 61 }

hmWanMbus4DVIF1C		OBJECT-TYPE
			SYNTAX	INTEGER
			MAX-ACCESS	read-only
			STATUS	current
			::= { hmWanMbus4D 62 }

hmWanMbus4DValue1C		OBJECT-TYPE
			SYNTAX	INTEGER
			MAX-ACCESS	read-only
			STATUS	current
			::= { hmWanMbus4D 63 }

hmWanMbus4DVIF1D		OBJECT-TYPE
			SYNTAX	INTEGER
			MAX-ACCESS	read-only
			STATUS	current
			::= { hmWanMbus4D 64 }

hmWanMbus4DValue1D		OBJECT-TYPE
			SYNTAX	INTEGER
			MAX-ACCESS	read-only
			STATUS	current
			::= { hmWanMbus4D 65 }

hmWanMbus4DVIF1E		OBJECT-TYPE
			SYNTAX	INTEGER
			MAX-ACCESS	read-only
			STATUS	current
			::= { hmWanMbus4D 66 }

hmWanMbus4DValue1E		OBJECT-TYPE
			SYNTAX	INTEGER
			MAX-ACCESS	read-only
			STATUS	current
			::= { hmWanMbus4D 67 }

hmWanMbus4DVIF1F		OBJECT-TYPE
			SYNTAX	INTEGER
			MAX-ACCESS	read-only
			STATUS	current
			::= { hmWanMbus4D 68 }

hmWanMbus4DValue1F		OBJECT-TYPE
			SYNTAX	INTEGER
			MAX-ACCESS	read-only
			STATUS	current
			::= { hmWanMbus4D 69 }

hmWanMbus4DVIF20		OBJECT-TYPE
			SYNTAX	INTEGER
			MAX-ACCESS	read-only
			STATUS	current
			::= { hmWanMbus4D 70 }

hmWanMbus4DValue20		OBJECT-TYPE
			SYNTAX	INTEGER
			MAX-ACCESS	read-only
			STATUS	current
			::= { hmWanMbus4D 71 }

hmWanMbus4DVIF21		OBJECT-TYPE
			SYNTAX	INTEGER
			MAX-ACCESS	read-only
			STATUS	current
			::= { hmWanMbus4D 72 }

hmWanMbus4DValue21		OBJECT-TYPE
			SYNTAX	INTEGER
			MAX-ACCESS	read-only
			STATUS	current
			::= { hmWanMbus4D 73 }

hmWanMbus4DVIF22		OBJECT-TYPE
			SYNTAX	INTEGER
			MAX-ACCESS	read-only
			STATUS	current
			::= { hmWanMbus4D 74 }

hmWanMbus4DValue22		OBJECT-TYPE
			SYNTAX	INTEGER
			MAX-ACCESS	read-only
			STATUS	current
			::= { hmWanMbus4D 75 }

hmWanMbus4DVIF23		OBJECT-TYPE
			SYNTAX	INTEGER
			MAX-ACCESS	read-only
			STATUS	current
			::= { hmWanMbus4D 76 }

hmWanMbus4DValue23		OBJECT-TYPE
			SYNTAX	INTEGER
			MAX-ACCESS	read-only
			STATUS	current
			::= { hmWanMbus4D 77 }

hmWanMbus4DVIF24		OBJECT-TYPE
			SYNTAX	INTEGER
			MAX-ACCESS	read-only
			STATUS	current
			::= { hmWanMbus4D 78 }

hmWanMbus4DValue24		OBJECT-TYPE
			SYNTAX	INTEGER
			MAX-ACCESS	read-only
			STATUS	current
			::= { hmWanMbus4D 79 }

hmWanMbus4DVIF25		OBJECT-TYPE
			SYNTAX	INTEGER
			MAX-ACCESS	read-only
			STATUS	current
			::= { hmWanMbus4D 80 }

hmWanMbus4DValue25		OBJECT-TYPE
			SYNTAX	INTEGER
			MAX-ACCESS	read-only
			STATUS	current
			::= { hmWanMbus4D 81 }

hmWanMbus4DVIF26		OBJECT-TYPE
			SYNTAX	INTEGER
			MAX-ACCESS	read-only
			STATUS	current
			::= { hmWanMbus4D 82 }

hmWanMbus4DValue26		OBJECT-TYPE
			SYNTAX	INTEGER
			MAX-ACCESS	read-only
			STATUS	current
			::= { hmWanMbus4D 83 }

hmWanMbus4DVIF27		OBJECT-TYPE
			SYNTAX	INTEGER
			MAX-ACCESS	read-only
			STATUS	current
			::= { hmWanMbus4D 84 }

hmWanMbus4DValue27		OBJECT-TYPE
			SYNTAX	INTEGER
			MAX-ACCESS	read-only
			STATUS	current
			::= { hmWanMbus4D 85 }

hmWanMbus4DVIF28		OBJECT-TYPE
			SYNTAX	INTEGER
			MAX-ACCESS	read-only
			STATUS	current
			::= { hmWanMbus4D 86 }

hmWanMbus4DValue28		OBJECT-TYPE
			SYNTAX	INTEGER
			MAX-ACCESS	read-only
			STATUS	current
			::= { hmWanMbus4D 87 }

hmWanMbus4DVIF29		OBJECT-TYPE
			SYNTAX	INTEGER
			MAX-ACCESS	read-only
			STATUS	current
			::= { hmWanMbus4D 88 }

hmWanMbus4DValue29		OBJECT-TYPE
			SYNTAX	INTEGER
			MAX-ACCESS	read-only
			STATUS	current
			::= { hmWanMbus4D 89 }

hmWanMbus4DVIF2A		OBJECT-TYPE
			SYNTAX	INTEGER
			MAX-ACCESS	read-only
			STATUS	current
			::= { hmWanMbus4D 90 }

hmWanMbus4DValue2A		OBJECT-TYPE
			SYNTAX	INTEGER
			MAX-ACCESS	read-only
			STATUS	current
			::= { hmWanMbus4D 91 }

hmWanMbus4DVIF2B		OBJECT-TYPE
			SYNTAX	INTEGER
			MAX-ACCESS	read-only
			STATUS	current
			::= { hmWanMbus4D 92 }

hmWanMbus4DValue2B		OBJECT-TYPE
			SYNTAX	INTEGER
			MAX-ACCESS	read-only
			STATUS	current
			::= { hmWanMbus4D 93 }

hmWanMbus4DVIF2C		OBJECT-TYPE
			SYNTAX	INTEGER
			MAX-ACCESS	read-only
			STATUS	current
			::= { hmWanMbus4D 94 }

hmWanMbus4DValue2C		OBJECT-TYPE
			SYNTAX	INTEGER
			MAX-ACCESS	read-only
			STATUS	current
			::= { hmWanMbus4D 95 }

hmWanMbus4DVIF2D		OBJECT-TYPE
			SYNTAX	INTEGER
			MAX-ACCESS	read-only
			STATUS	current
			::= { hmWanMbus4D 96 }

hmWanMbus4DValue2D		OBJECT-TYPE
			SYNTAX	INTEGER
			MAX-ACCESS	read-only
			STATUS	current
			::= { hmWanMbus4D 97 }

hmWanMbus4DVIF2E		OBJECT-TYPE
			SYNTAX	INTEGER
			MAX-ACCESS	read-only
			STATUS	current
			::= { hmWanMbus4D 98 }

hmWanMbus4DValue2E		OBJECT-TYPE
			SYNTAX	INTEGER
			MAX-ACCESS	read-only
			STATUS	current
			::= { hmWanMbus4D 99 }

hmWanMbus4DVIF2F		OBJECT-TYPE
			SYNTAX	INTEGER
			MAX-ACCESS	read-only
			STATUS	current
			::= { hmWanMbus4D 100 }

hmWanMbus4DValue2F		OBJECT-TYPE
			SYNTAX	INTEGER
			MAX-ACCESS	read-only
			STATUS	current
			::= { hmWanMbus4D 101 }

hmWanMbus4E			OBJECT IDENTIFIER ::= { hmWanMbus 78 }

hmWanMbus4EIdNumber		OBJECT-TYPE
			SYNTAX	Gauge32
			MAX-ACCESS	read-only
			STATUS	current
			::= { hmWanMbus4E 1 }

hmWanMbus4EManufacturer	OBJECT-TYPE
			SYNTAX	Gauge32
			MAX-ACCESS	read-only
			STATUS	current
			::= { hmWanMbus4E 2 }

hmWanMbus4EVersion		OBJECT-TYPE
			SYNTAX	Gauge32
			MAX-ACCESS	read-only
			STATUS	current
			::= { hmWanMbus4E 3 }

hmWanMbus4EMedium		OBJECT-TYPE
			SYNTAX	Gauge32
			MAX-ACCESS	read-only
			STATUS	current
			::= { hmWanMbus4E 4 }

hmWanMbus4EStatus		OBJECT-TYPE
			SYNTAX	Gauge32
			MAX-ACCESS	read-only
			STATUS	current
			::= { hmWanMbus4E 5 }

hmWanMbus4EVIF00		OBJECT-TYPE
			SYNTAX	INTEGER
			MAX-ACCESS	read-only
			STATUS	current
			::= { hmWanMbus4E 6 }

hmWanMbus4EValue00		OBJECT-TYPE
			SYNTAX	INTEGER
			MAX-ACCESS	read-only
			STATUS	current
			::= { hmWanMbus4E 7 }

hmWanMbus4EVIF01		OBJECT-TYPE
			SYNTAX	INTEGER
			MAX-ACCESS	read-only
			STATUS	current
			::= { hmWanMbus4E 8 }

hmWanMbus4EValue01		OBJECT-TYPE
			SYNTAX	INTEGER
			MAX-ACCESS	read-only
			STATUS	current
			::= { hmWanMbus4E 9 }

hmWanMbus4EVIF02		OBJECT-TYPE
			SYNTAX	INTEGER
			MAX-ACCESS	read-only
			STATUS	current
			::= { hmWanMbus4E 10 }

hmWanMbus4EValue02		OBJECT-TYPE
			SYNTAX	INTEGER
			MAX-ACCESS	read-only
			STATUS	current
			::= { hmWanMbus4E 11 }

hmWanMbus4EVIF03		OBJECT-TYPE
			SYNTAX	INTEGER
			MAX-ACCESS	read-only
			STATUS	current
			::= { hmWanMbus4E 12 }

hmWanMbus4EValue03		OBJECT-TYPE
			SYNTAX	INTEGER
			MAX-ACCESS	read-only
			STATUS	current
			::= { hmWanMbus4E 13 }

hmWanMbus4EVIF04		OBJECT-TYPE
			SYNTAX	INTEGER
			MAX-ACCESS	read-only
			STATUS	current
			::= { hmWanMbus4E 14 }

hmWanMbus4EValue04		OBJECT-TYPE
			SYNTAX	INTEGER
			MAX-ACCESS	read-only
			STATUS	current
			::= { hmWanMbus4E 15 }

hmWanMbus4EVIF05		OBJECT-TYPE
			SYNTAX	INTEGER
			MAX-ACCESS	read-only
			STATUS	current
			::= { hmWanMbus4E 16 }

hmWanMbus4EValue05		OBJECT-TYPE
			SYNTAX	INTEGER
			MAX-ACCESS	read-only
			STATUS	current
			::= { hmWanMbus4E 17 }

hmWanMbus4EVIF06		OBJECT-TYPE
			SYNTAX	INTEGER
			MAX-ACCESS	read-only
			STATUS	current
			::= { hmWanMbus4E 18 }

hmWanMbus4EValue06		OBJECT-TYPE
			SYNTAX	INTEGER
			MAX-ACCESS	read-only
			STATUS	current
			::= { hmWanMbus4E 19 }

hmWanMbus4EVIF07		OBJECT-TYPE
			SYNTAX	INTEGER
			MAX-ACCESS	read-only
			STATUS	current
			::= { hmWanMbus4E 20 }

hmWanMbus4EValue07		OBJECT-TYPE
			SYNTAX	INTEGER
			MAX-ACCESS	read-only
			STATUS	current
			::= { hmWanMbus4E 21 }

hmWanMbus4EVIF08		OBJECT-TYPE
			SYNTAX	INTEGER
			MAX-ACCESS	read-only
			STATUS	current
			::= { hmWanMbus4E 22 }

hmWanMbus4EValue08		OBJECT-TYPE
			SYNTAX	INTEGER
			MAX-ACCESS	read-only
			STATUS	current
			::= { hmWanMbus4E 23 }

hmWanMbus4EVIF09		OBJECT-TYPE
			SYNTAX	INTEGER
			MAX-ACCESS	read-only
			STATUS	current
			::= { hmWanMbus4E 24 }

hmWanMbus4EValue09		OBJECT-TYPE
			SYNTAX	INTEGER
			MAX-ACCESS	read-only
			STATUS	current
			::= { hmWanMbus4E 25 }

hmWanMbus4EVIF0A		OBJECT-TYPE
			SYNTAX	INTEGER
			MAX-ACCESS	read-only
			STATUS	current
			::= { hmWanMbus4E 26 }

hmWanMbus4EValue0A		OBJECT-TYPE
			SYNTAX	INTEGER
			MAX-ACCESS	read-only
			STATUS	current
			::= { hmWanMbus4E 27 }

hmWanMbus4EVIF0B		OBJECT-TYPE
			SYNTAX	INTEGER
			MAX-ACCESS	read-only
			STATUS	current
			::= { hmWanMbus4E 28 }

hmWanMbus4EValue0B		OBJECT-TYPE
			SYNTAX	INTEGER
			MAX-ACCESS	read-only
			STATUS	current
			::= { hmWanMbus4E 29 }

hmWanMbus4EVIF0C		OBJECT-TYPE
			SYNTAX	INTEGER
			MAX-ACCESS	read-only
			STATUS	current
			::= { hmWanMbus4E 30 }

hmWanMbus4EValue0C		OBJECT-TYPE
			SYNTAX	INTEGER
			MAX-ACCESS	read-only
			STATUS	current
			::= { hmWanMbus4E 31 }

hmWanMbus4EVIF0D		OBJECT-TYPE
			SYNTAX	INTEGER
			MAX-ACCESS	read-only
			STATUS	current
			::= { hmWanMbus4E 32 }

hmWanMbus4EValue0D		OBJECT-TYPE
			SYNTAX	INTEGER
			MAX-ACCESS	read-only
			STATUS	current
			::= { hmWanMbus4E 33 }

hmWanMbus4EVIF0E		OBJECT-TYPE
			SYNTAX	INTEGER
			MAX-ACCESS	read-only
			STATUS	current
			::= { hmWanMbus4E 34 }

hmWanMbus4EValue0E		OBJECT-TYPE
			SYNTAX	INTEGER
			MAX-ACCESS	read-only
			STATUS	current
			::= { hmWanMbus4E 35 }

hmWanMbus4EVIF0F		OBJECT-TYPE
			SYNTAX	INTEGER
			MAX-ACCESS	read-only
			STATUS	current
			::= { hmWanMbus4E 36 }

hmWanMbus4EValue0F		OBJECT-TYPE
			SYNTAX	INTEGER
			MAX-ACCESS	read-only
			STATUS	current
			::= { hmWanMbus4E 37 }

hmWanMbus4EVIF10		OBJECT-TYPE
			SYNTAX	INTEGER
			MAX-ACCESS	read-only
			STATUS	current
			::= { hmWanMbus4E 38 }

hmWanMbus4EValue10		OBJECT-TYPE
			SYNTAX	INTEGER
			MAX-ACCESS	read-only
			STATUS	current
			::= { hmWanMbus4E 39 }

hmWanMbus4EVIF11		OBJECT-TYPE
			SYNTAX	INTEGER
			MAX-ACCESS	read-only
			STATUS	current
			::= { hmWanMbus4E 40 }

hmWanMbus4EValue11		OBJECT-TYPE
			SYNTAX	INTEGER
			MAX-ACCESS	read-only
			STATUS	current
			::= { hmWanMbus4E 41 }

hmWanMbus4EVIF12		OBJECT-TYPE
			SYNTAX	INTEGER
			MAX-ACCESS	read-only
			STATUS	current
			::= { hmWanMbus4E 42 }

hmWanMbus4EValue12		OBJECT-TYPE
			SYNTAX	INTEGER
			MAX-ACCESS	read-only
			STATUS	current
			::= { hmWanMbus4E 43 }

hmWanMbus4EVIF13		OBJECT-TYPE
			SYNTAX	INTEGER
			MAX-ACCESS	read-only
			STATUS	current
			::= { hmWanMbus4E 44 }

hmWanMbus4EValue13		OBJECT-TYPE
			SYNTAX	INTEGER
			MAX-ACCESS	read-only
			STATUS	current
			::= { hmWanMbus4E 45 }

hmWanMbus4EVIF14		OBJECT-TYPE
			SYNTAX	INTEGER
			MAX-ACCESS	read-only
			STATUS	current
			::= { hmWanMbus4E 46 }

hmWanMbus4EValue14		OBJECT-TYPE
			SYNTAX	INTEGER
			MAX-ACCESS	read-only
			STATUS	current
			::= { hmWanMbus4E 47 }

hmWanMbus4EVIF15		OBJECT-TYPE
			SYNTAX	INTEGER
			MAX-ACCESS	read-only
			STATUS	current
			::= { hmWanMbus4E 48 }

hmWanMbus4EValue15		OBJECT-TYPE
			SYNTAX	INTEGER
			MAX-ACCESS	read-only
			STATUS	current
			::= { hmWanMbus4E 49 }

hmWanMbus4EVIF16		OBJECT-TYPE
			SYNTAX	INTEGER
			MAX-ACCESS	read-only
			STATUS	current
			::= { hmWanMbus4E 50 }

hmWanMbus4EValue16		OBJECT-TYPE
			SYNTAX	INTEGER
			MAX-ACCESS	read-only
			STATUS	current
			::= { hmWanMbus4E 51 }

hmWanMbus4EVIF17		OBJECT-TYPE
			SYNTAX	INTEGER
			MAX-ACCESS	read-only
			STATUS	current
			::= { hmWanMbus4E 52 }

hmWanMbus4EValue17		OBJECT-TYPE
			SYNTAX	INTEGER
			MAX-ACCESS	read-only
			STATUS	current
			::= { hmWanMbus4E 53 }

hmWanMbus4EVIF18		OBJECT-TYPE
			SYNTAX	INTEGER
			MAX-ACCESS	read-only
			STATUS	current
			::= { hmWanMbus4E 54 }

hmWanMbus4EValue18		OBJECT-TYPE
			SYNTAX	INTEGER
			MAX-ACCESS	read-only
			STATUS	current
			::= { hmWanMbus4E 55 }

hmWanMbus4EVIF19		OBJECT-TYPE
			SYNTAX	INTEGER
			MAX-ACCESS	read-only
			STATUS	current
			::= { hmWanMbus4E 56 }

hmWanMbus4EValue19		OBJECT-TYPE
			SYNTAX	INTEGER
			MAX-ACCESS	read-only
			STATUS	current
			::= { hmWanMbus4E 57 }

hmWanMbus4EVIF1A		OBJECT-TYPE
			SYNTAX	INTEGER
			MAX-ACCESS	read-only
			STATUS	current
			::= { hmWanMbus4E 58 }

hmWanMbus4EValue1A		OBJECT-TYPE
			SYNTAX	INTEGER
			MAX-ACCESS	read-only
			STATUS	current
			::= { hmWanMbus4E 59 }

hmWanMbus4EVIF1B		OBJECT-TYPE
			SYNTAX	INTEGER
			MAX-ACCESS	read-only
			STATUS	current
			::= { hmWanMbus4E 60 }

hmWanMbus4EValue1B		OBJECT-TYPE
			SYNTAX	INTEGER
			MAX-ACCESS	read-only
			STATUS	current
			::= { hmWanMbus4E 61 }

hmWanMbus4EVIF1C		OBJECT-TYPE
			SYNTAX	INTEGER
			MAX-ACCESS	read-only
			STATUS	current
			::= { hmWanMbus4E 62 }

hmWanMbus4EValue1C		OBJECT-TYPE
			SYNTAX	INTEGER
			MAX-ACCESS	read-only
			STATUS	current
			::= { hmWanMbus4E 63 }

hmWanMbus4EVIF1D		OBJECT-TYPE
			SYNTAX	INTEGER
			MAX-ACCESS	read-only
			STATUS	current
			::= { hmWanMbus4E 64 }

hmWanMbus4EValue1D		OBJECT-TYPE
			SYNTAX	INTEGER
			MAX-ACCESS	read-only
			STATUS	current
			::= { hmWanMbus4E 65 }

hmWanMbus4EVIF1E		OBJECT-TYPE
			SYNTAX	INTEGER
			MAX-ACCESS	read-only
			STATUS	current
			::= { hmWanMbus4E 66 }

hmWanMbus4EValue1E		OBJECT-TYPE
			SYNTAX	INTEGER
			MAX-ACCESS	read-only
			STATUS	current
			::= { hmWanMbus4E 67 }

hmWanMbus4EVIF1F		OBJECT-TYPE
			SYNTAX	INTEGER
			MAX-ACCESS	read-only
			STATUS	current
			::= { hmWanMbus4E 68 }

hmWanMbus4EValue1F		OBJECT-TYPE
			SYNTAX	INTEGER
			MAX-ACCESS	read-only
			STATUS	current
			::= { hmWanMbus4E 69 }

hmWanMbus4EVIF20		OBJECT-TYPE
			SYNTAX	INTEGER
			MAX-ACCESS	read-only
			STATUS	current
			::= { hmWanMbus4E 70 }

hmWanMbus4EValue20		OBJECT-TYPE
			SYNTAX	INTEGER
			MAX-ACCESS	read-only
			STATUS	current
			::= { hmWanMbus4E 71 }

hmWanMbus4EVIF21		OBJECT-TYPE
			SYNTAX	INTEGER
			MAX-ACCESS	read-only
			STATUS	current
			::= { hmWanMbus4E 72 }

hmWanMbus4EValue21		OBJECT-TYPE
			SYNTAX	INTEGER
			MAX-ACCESS	read-only
			STATUS	current
			::= { hmWanMbus4E 73 }

hmWanMbus4EVIF22		OBJECT-TYPE
			SYNTAX	INTEGER
			MAX-ACCESS	read-only
			STATUS	current
			::= { hmWanMbus4E 74 }

hmWanMbus4EValue22		OBJECT-TYPE
			SYNTAX	INTEGER
			MAX-ACCESS	read-only
			STATUS	current
			::= { hmWanMbus4E 75 }

hmWanMbus4EVIF23		OBJECT-TYPE
			SYNTAX	INTEGER
			MAX-ACCESS	read-only
			STATUS	current
			::= { hmWanMbus4E 76 }

hmWanMbus4EValue23		OBJECT-TYPE
			SYNTAX	INTEGER
			MAX-ACCESS	read-only
			STATUS	current
			::= { hmWanMbus4E 77 }

hmWanMbus4EVIF24		OBJECT-TYPE
			SYNTAX	INTEGER
			MAX-ACCESS	read-only
			STATUS	current
			::= { hmWanMbus4E 78 }

hmWanMbus4EValue24		OBJECT-TYPE
			SYNTAX	INTEGER
			MAX-ACCESS	read-only
			STATUS	current
			::= { hmWanMbus4E 79 }

hmWanMbus4EVIF25		OBJECT-TYPE
			SYNTAX	INTEGER
			MAX-ACCESS	read-only
			STATUS	current
			::= { hmWanMbus4E 80 }

hmWanMbus4EValue25		OBJECT-TYPE
			SYNTAX	INTEGER
			MAX-ACCESS	read-only
			STATUS	current
			::= { hmWanMbus4E 81 }

hmWanMbus4EVIF26		OBJECT-TYPE
			SYNTAX	INTEGER
			MAX-ACCESS	read-only
			STATUS	current
			::= { hmWanMbus4E 82 }

hmWanMbus4EValue26		OBJECT-TYPE
			SYNTAX	INTEGER
			MAX-ACCESS	read-only
			STATUS	current
			::= { hmWanMbus4E 83 }

hmWanMbus4EVIF27		OBJECT-TYPE
			SYNTAX	INTEGER
			MAX-ACCESS	read-only
			STATUS	current
			::= { hmWanMbus4E 84 }

hmWanMbus4EValue27		OBJECT-TYPE
			SYNTAX	INTEGER
			MAX-ACCESS	read-only
			STATUS	current
			::= { hmWanMbus4E 85 }

hmWanMbus4EVIF28		OBJECT-TYPE
			SYNTAX	INTEGER
			MAX-ACCESS	read-only
			STATUS	current
			::= { hmWanMbus4E 86 }

hmWanMbus4EValue28		OBJECT-TYPE
			SYNTAX	INTEGER
			MAX-ACCESS	read-only
			STATUS	current
			::= { hmWanMbus4E 87 }

hmWanMbus4EVIF29		OBJECT-TYPE
			SYNTAX	INTEGER
			MAX-ACCESS	read-only
			STATUS	current
			::= { hmWanMbus4E 88 }

hmWanMbus4EValue29		OBJECT-TYPE
			SYNTAX	INTEGER
			MAX-ACCESS	read-only
			STATUS	current
			::= { hmWanMbus4E 89 }

hmWanMbus4EVIF2A		OBJECT-TYPE
			SYNTAX	INTEGER
			MAX-ACCESS	read-only
			STATUS	current
			::= { hmWanMbus4E 90 }

hmWanMbus4EValue2A		OBJECT-TYPE
			SYNTAX	INTEGER
			MAX-ACCESS	read-only
			STATUS	current
			::= { hmWanMbus4E 91 }

hmWanMbus4EVIF2B		OBJECT-TYPE
			SYNTAX	INTEGER
			MAX-ACCESS	read-only
			STATUS	current
			::= { hmWanMbus4E 92 }

hmWanMbus4EValue2B		OBJECT-TYPE
			SYNTAX	INTEGER
			MAX-ACCESS	read-only
			STATUS	current
			::= { hmWanMbus4E 93 }

hmWanMbus4EVIF2C		OBJECT-TYPE
			SYNTAX	INTEGER
			MAX-ACCESS	read-only
			STATUS	current
			::= { hmWanMbus4E 94 }

hmWanMbus4EValue2C		OBJECT-TYPE
			SYNTAX	INTEGER
			MAX-ACCESS	read-only
			STATUS	current
			::= { hmWanMbus4E 95 }

hmWanMbus4EVIF2D		OBJECT-TYPE
			SYNTAX	INTEGER
			MAX-ACCESS	read-only
			STATUS	current
			::= { hmWanMbus4E 96 }

hmWanMbus4EValue2D		OBJECT-TYPE
			SYNTAX	INTEGER
			MAX-ACCESS	read-only
			STATUS	current
			::= { hmWanMbus4E 97 }

hmWanMbus4EVIF2E		OBJECT-TYPE
			SYNTAX	INTEGER
			MAX-ACCESS	read-only
			STATUS	current
			::= { hmWanMbus4E 98 }

hmWanMbus4EValue2E		OBJECT-TYPE
			SYNTAX	INTEGER
			MAX-ACCESS	read-only
			STATUS	current
			::= { hmWanMbus4E 99 }

hmWanMbus4EVIF2F		OBJECT-TYPE
			SYNTAX	INTEGER
			MAX-ACCESS	read-only
			STATUS	current
			::= { hmWanMbus4E 100 }

hmWanMbus4EValue2F		OBJECT-TYPE
			SYNTAX	INTEGER
			MAX-ACCESS	read-only
			STATUS	current
			::= { hmWanMbus4E 101 }

hmWanMbus4F			OBJECT IDENTIFIER ::= { hmWanMbus 79 }

hmWanMbus4FIdNumber		OBJECT-TYPE
			SYNTAX	Gauge32
			MAX-ACCESS	read-only
			STATUS	current
			::= { hmWanMbus4F 1 }

hmWanMbus4FManufacturer	OBJECT-TYPE
			SYNTAX	Gauge32
			MAX-ACCESS	read-only
			STATUS	current
			::= { hmWanMbus4F 2 }

hmWanMbus4FVersion		OBJECT-TYPE
			SYNTAX	Gauge32
			MAX-ACCESS	read-only
			STATUS	current
			::= { hmWanMbus4F 3 }

hmWanMbus4FMedium		OBJECT-TYPE
			SYNTAX	Gauge32
			MAX-ACCESS	read-only
			STATUS	current
			::= { hmWanMbus4F 4 }

hmWanMbus4FStatus		OBJECT-TYPE
			SYNTAX	Gauge32
			MAX-ACCESS	read-only
			STATUS	current
			::= { hmWanMbus4F 5 }

hmWanMbus4FVIF00		OBJECT-TYPE
			SYNTAX	INTEGER
			MAX-ACCESS	read-only
			STATUS	current
			::= { hmWanMbus4F 6 }

hmWanMbus4FValue00		OBJECT-TYPE
			SYNTAX	INTEGER
			MAX-ACCESS	read-only
			STATUS	current
			::= { hmWanMbus4F 7 }

hmWanMbus4FVIF01		OBJECT-TYPE
			SYNTAX	INTEGER
			MAX-ACCESS	read-only
			STATUS	current
			::= { hmWanMbus4F 8 }

hmWanMbus4FValue01		OBJECT-TYPE
			SYNTAX	INTEGER
			MAX-ACCESS	read-only
			STATUS	current
			::= { hmWanMbus4F 9 }

hmWanMbus4FVIF02		OBJECT-TYPE
			SYNTAX	INTEGER
			MAX-ACCESS	read-only
			STATUS	current
			::= { hmWanMbus4F 10 }

hmWanMbus4FValue02		OBJECT-TYPE
			SYNTAX	INTEGER
			MAX-ACCESS	read-only
			STATUS	current
			::= { hmWanMbus4F 11 }

hmWanMbus4FVIF03		OBJECT-TYPE
			SYNTAX	INTEGER
			MAX-ACCESS	read-only
			STATUS	current
			::= { hmWanMbus4F 12 }

hmWanMbus4FValue03		OBJECT-TYPE
			SYNTAX	INTEGER
			MAX-ACCESS	read-only
			STATUS	current
			::= { hmWanMbus4F 13 }

hmWanMbus4FVIF04		OBJECT-TYPE
			SYNTAX	INTEGER
			MAX-ACCESS	read-only
			STATUS	current
			::= { hmWanMbus4F 14 }

hmWanMbus4FValue04		OBJECT-TYPE
			SYNTAX	INTEGER
			MAX-ACCESS	read-only
			STATUS	current
			::= { hmWanMbus4F 15 }

hmWanMbus4FVIF05		OBJECT-TYPE
			SYNTAX	INTEGER
			MAX-ACCESS	read-only
			STATUS	current
			::= { hmWanMbus4F 16 }

hmWanMbus4FValue05		OBJECT-TYPE
			SYNTAX	INTEGER
			MAX-ACCESS	read-only
			STATUS	current
			::= { hmWanMbus4F 17 }

hmWanMbus4FVIF06		OBJECT-TYPE
			SYNTAX	INTEGER
			MAX-ACCESS	read-only
			STATUS	current
			::= { hmWanMbus4F 18 }

hmWanMbus4FValue06		OBJECT-TYPE
			SYNTAX	INTEGER
			MAX-ACCESS	read-only
			STATUS	current
			::= { hmWanMbus4F 19 }

hmWanMbus4FVIF07		OBJECT-TYPE
			SYNTAX	INTEGER
			MAX-ACCESS	read-only
			STATUS	current
			::= { hmWanMbus4F 20 }

hmWanMbus4FValue07		OBJECT-TYPE
			SYNTAX	INTEGER
			MAX-ACCESS	read-only
			STATUS	current
			::= { hmWanMbus4F 21 }

hmWanMbus4FVIF08		OBJECT-TYPE
			SYNTAX	INTEGER
			MAX-ACCESS	read-only
			STATUS	current
			::= { hmWanMbus4F 22 }

hmWanMbus4FValue08		OBJECT-TYPE
			SYNTAX	INTEGER
			MAX-ACCESS	read-only
			STATUS	current
			::= { hmWanMbus4F 23 }

hmWanMbus4FVIF09		OBJECT-TYPE
			SYNTAX	INTEGER
			MAX-ACCESS	read-only
			STATUS	current
			::= { hmWanMbus4F 24 }

hmWanMbus4FValue09		OBJECT-TYPE
			SYNTAX	INTEGER
			MAX-ACCESS	read-only
			STATUS	current
			::= { hmWanMbus4F 25 }

hmWanMbus4FVIF0A		OBJECT-TYPE
			SYNTAX	INTEGER
			MAX-ACCESS	read-only
			STATUS	current
			::= { hmWanMbus4F 26 }

hmWanMbus4FValue0A		OBJECT-TYPE
			SYNTAX	INTEGER
			MAX-ACCESS	read-only
			STATUS	current
			::= { hmWanMbus4F 27 }

hmWanMbus4FVIF0B		OBJECT-TYPE
			SYNTAX	INTEGER
			MAX-ACCESS	read-only
			STATUS	current
			::= { hmWanMbus4F 28 }

hmWanMbus4FValue0B		OBJECT-TYPE
			SYNTAX	INTEGER
			MAX-ACCESS	read-only
			STATUS	current
			::= { hmWanMbus4F 29 }

hmWanMbus4FVIF0C		OBJECT-TYPE
			SYNTAX	INTEGER
			MAX-ACCESS	read-only
			STATUS	current
			::= { hmWanMbus4F 30 }

hmWanMbus4FValue0C		OBJECT-TYPE
			SYNTAX	INTEGER
			MAX-ACCESS	read-only
			STATUS	current
			::= { hmWanMbus4F 31 }

hmWanMbus4FVIF0D		OBJECT-TYPE
			SYNTAX	INTEGER
			MAX-ACCESS	read-only
			STATUS	current
			::= { hmWanMbus4F 32 }

hmWanMbus4FValue0D		OBJECT-TYPE
			SYNTAX	INTEGER
			MAX-ACCESS	read-only
			STATUS	current
			::= { hmWanMbus4F 33 }

hmWanMbus4FVIF0E		OBJECT-TYPE
			SYNTAX	INTEGER
			MAX-ACCESS	read-only
			STATUS	current
			::= { hmWanMbus4F 34 }

hmWanMbus4FValue0E		OBJECT-TYPE
			SYNTAX	INTEGER
			MAX-ACCESS	read-only
			STATUS	current
			::= { hmWanMbus4F 35 }

hmWanMbus4FVIF0F		OBJECT-TYPE
			SYNTAX	INTEGER
			MAX-ACCESS	read-only
			STATUS	current
			::= { hmWanMbus4F 36 }

hmWanMbus4FValue0F		OBJECT-TYPE
			SYNTAX	INTEGER
			MAX-ACCESS	read-only
			STATUS	current
			::= { hmWanMbus4F 37 }

hmWanMbus4FVIF10		OBJECT-TYPE
			SYNTAX	INTEGER
			MAX-ACCESS	read-only
			STATUS	current
			::= { hmWanMbus4F 38 }

hmWanMbus4FValue10		OBJECT-TYPE
			SYNTAX	INTEGER
			MAX-ACCESS	read-only
			STATUS	current
			::= { hmWanMbus4F 39 }

hmWanMbus4FVIF11		OBJECT-TYPE
			SYNTAX	INTEGER
			MAX-ACCESS	read-only
			STATUS	current
			::= { hmWanMbus4F 40 }

hmWanMbus4FValue11		OBJECT-TYPE
			SYNTAX	INTEGER
			MAX-ACCESS	read-only
			STATUS	current
			::= { hmWanMbus4F 41 }

hmWanMbus4FVIF12		OBJECT-TYPE
			SYNTAX	INTEGER
			MAX-ACCESS	read-only
			STATUS	current
			::= { hmWanMbus4F 42 }

hmWanMbus4FValue12		OBJECT-TYPE
			SYNTAX	INTEGER
			MAX-ACCESS	read-only
			STATUS	current
			::= { hmWanMbus4F 43 }

hmWanMbus4FVIF13		OBJECT-TYPE
			SYNTAX	INTEGER
			MAX-ACCESS	read-only
			STATUS	current
			::= { hmWanMbus4F 44 }

hmWanMbus4FValue13		OBJECT-TYPE
			SYNTAX	INTEGER
			MAX-ACCESS	read-only
			STATUS	current
			::= { hmWanMbus4F 45 }

hmWanMbus4FVIF14		OBJECT-TYPE
			SYNTAX	INTEGER
			MAX-ACCESS	read-only
			STATUS	current
			::= { hmWanMbus4F 46 }

hmWanMbus4FValue14		OBJECT-TYPE
			SYNTAX	INTEGER
			MAX-ACCESS	read-only
			STATUS	current
			::= { hmWanMbus4F 47 }

hmWanMbus4FVIF15		OBJECT-TYPE
			SYNTAX	INTEGER
			MAX-ACCESS	read-only
			STATUS	current
			::= { hmWanMbus4F 48 }

hmWanMbus4FValue15		OBJECT-TYPE
			SYNTAX	INTEGER
			MAX-ACCESS	read-only
			STATUS	current
			::= { hmWanMbus4F 49 }

hmWanMbus4FVIF16		OBJECT-TYPE
			SYNTAX	INTEGER
			MAX-ACCESS	read-only
			STATUS	current
			::= { hmWanMbus4F 50 }

hmWanMbus4FValue16		OBJECT-TYPE
			SYNTAX	INTEGER
			MAX-ACCESS	read-only
			STATUS	current
			::= { hmWanMbus4F 51 }

hmWanMbus4FVIF17		OBJECT-TYPE
			SYNTAX	INTEGER
			MAX-ACCESS	read-only
			STATUS	current
			::= { hmWanMbus4F 52 }

hmWanMbus4FValue17		OBJECT-TYPE
			SYNTAX	INTEGER
			MAX-ACCESS	read-only
			STATUS	current
			::= { hmWanMbus4F 53 }

hmWanMbus4FVIF18		OBJECT-TYPE
			SYNTAX	INTEGER
			MAX-ACCESS	read-only
			STATUS	current
			::= { hmWanMbus4F 54 }

hmWanMbus4FValue18		OBJECT-TYPE
			SYNTAX	INTEGER
			MAX-ACCESS	read-only
			STATUS	current
			::= { hmWanMbus4F 55 }

hmWanMbus4FVIF19		OBJECT-TYPE
			SYNTAX	INTEGER
			MAX-ACCESS	read-only
			STATUS	current
			::= { hmWanMbus4F 56 }

hmWanMbus4FValue19		OBJECT-TYPE
			SYNTAX	INTEGER
			MAX-ACCESS	read-only
			STATUS	current
			::= { hmWanMbus4F 57 }

hmWanMbus4FVIF1A		OBJECT-TYPE
			SYNTAX	INTEGER
			MAX-ACCESS	read-only
			STATUS	current
			::= { hmWanMbus4F 58 }

hmWanMbus4FValue1A		OBJECT-TYPE
			SYNTAX	INTEGER
			MAX-ACCESS	read-only
			STATUS	current
			::= { hmWanMbus4F 59 }

hmWanMbus4FVIF1B		OBJECT-TYPE
			SYNTAX	INTEGER
			MAX-ACCESS	read-only
			STATUS	current
			::= { hmWanMbus4F 60 }

hmWanMbus4FValue1B		OBJECT-TYPE
			SYNTAX	INTEGER
			MAX-ACCESS	read-only
			STATUS	current
			::= { hmWanMbus4F 61 }

hmWanMbus4FVIF1C		OBJECT-TYPE
			SYNTAX	INTEGER
			MAX-ACCESS	read-only
			STATUS	current
			::= { hmWanMbus4F 62 }

hmWanMbus4FValue1C		OBJECT-TYPE
			SYNTAX	INTEGER
			MAX-ACCESS	read-only
			STATUS	current
			::= { hmWanMbus4F 63 }

hmWanMbus4FVIF1D		OBJECT-TYPE
			SYNTAX	INTEGER
			MAX-ACCESS	read-only
			STATUS	current
			::= { hmWanMbus4F 64 }

hmWanMbus4FValue1D		OBJECT-TYPE
			SYNTAX	INTEGER
			MAX-ACCESS	read-only
			STATUS	current
			::= { hmWanMbus4F 65 }

hmWanMbus4FVIF1E		OBJECT-TYPE
			SYNTAX	INTEGER
			MAX-ACCESS	read-only
			STATUS	current
			::= { hmWanMbus4F 66 }

hmWanMbus4FValue1E		OBJECT-TYPE
			SYNTAX	INTEGER
			MAX-ACCESS	read-only
			STATUS	current
			::= { hmWanMbus4F 67 }

hmWanMbus4FVIF1F		OBJECT-TYPE
			SYNTAX	INTEGER
			MAX-ACCESS	read-only
			STATUS	current
			::= { hmWanMbus4F 68 }

hmWanMbus4FValue1F		OBJECT-TYPE
			SYNTAX	INTEGER
			MAX-ACCESS	read-only
			STATUS	current
			::= { hmWanMbus4F 69 }

hmWanMbus4FVIF20		OBJECT-TYPE
			SYNTAX	INTEGER
			MAX-ACCESS	read-only
			STATUS	current
			::= { hmWanMbus4F 70 }

hmWanMbus4FValue20		OBJECT-TYPE
			SYNTAX	INTEGER
			MAX-ACCESS	read-only
			STATUS	current
			::= { hmWanMbus4F 71 }

hmWanMbus4FVIF21		OBJECT-TYPE
			SYNTAX	INTEGER
			MAX-ACCESS	read-only
			STATUS	current
			::= { hmWanMbus4F 72 }

hmWanMbus4FValue21		OBJECT-TYPE
			SYNTAX	INTEGER
			MAX-ACCESS	read-only
			STATUS	current
			::= { hmWanMbus4F 73 }

hmWanMbus4FVIF22		OBJECT-TYPE
			SYNTAX	INTEGER
			MAX-ACCESS	read-only
			STATUS	current
			::= { hmWanMbus4F 74 }

hmWanMbus4FValue22		OBJECT-TYPE
			SYNTAX	INTEGER
			MAX-ACCESS	read-only
			STATUS	current
			::= { hmWanMbus4F 75 }

hmWanMbus4FVIF23		OBJECT-TYPE
			SYNTAX	INTEGER
			MAX-ACCESS	read-only
			STATUS	current
			::= { hmWanMbus4F 76 }

hmWanMbus4FValue23		OBJECT-TYPE
			SYNTAX	INTEGER
			MAX-ACCESS	read-only
			STATUS	current
			::= { hmWanMbus4F 77 }

hmWanMbus4FVIF24		OBJECT-TYPE
			SYNTAX	INTEGER
			MAX-ACCESS	read-only
			STATUS	current
			::= { hmWanMbus4F 78 }

hmWanMbus4FValue24		OBJECT-TYPE
			SYNTAX	INTEGER
			MAX-ACCESS	read-only
			STATUS	current
			::= { hmWanMbus4F 79 }

hmWanMbus4FVIF25		OBJECT-TYPE
			SYNTAX	INTEGER
			MAX-ACCESS	read-only
			STATUS	current
			::= { hmWanMbus4F 80 }

hmWanMbus4FValue25		OBJECT-TYPE
			SYNTAX	INTEGER
			MAX-ACCESS	read-only
			STATUS	current
			::= { hmWanMbus4F 81 }

hmWanMbus4FVIF26		OBJECT-TYPE
			SYNTAX	INTEGER
			MAX-ACCESS	read-only
			STATUS	current
			::= { hmWanMbus4F 82 }

hmWanMbus4FValue26		OBJECT-TYPE
			SYNTAX	INTEGER
			MAX-ACCESS	read-only
			STATUS	current
			::= { hmWanMbus4F 83 }

hmWanMbus4FVIF27		OBJECT-TYPE
			SYNTAX	INTEGER
			MAX-ACCESS	read-only
			STATUS	current
			::= { hmWanMbus4F 84 }

hmWanMbus4FValue27		OBJECT-TYPE
			SYNTAX	INTEGER
			MAX-ACCESS	read-only
			STATUS	current
			::= { hmWanMbus4F 85 }

hmWanMbus4FVIF28		OBJECT-TYPE
			SYNTAX	INTEGER
			MAX-ACCESS	read-only
			STATUS	current
			::= { hmWanMbus4F 86 }

hmWanMbus4FValue28		OBJECT-TYPE
			SYNTAX	INTEGER
			MAX-ACCESS	read-only
			STATUS	current
			::= { hmWanMbus4F 87 }

hmWanMbus4FVIF29		OBJECT-TYPE
			SYNTAX	INTEGER
			MAX-ACCESS	read-only
			STATUS	current
			::= { hmWanMbus4F 88 }

hmWanMbus4FValue29		OBJECT-TYPE
			SYNTAX	INTEGER
			MAX-ACCESS	read-only
			STATUS	current
			::= { hmWanMbus4F 89 }

hmWanMbus4FVIF2A		OBJECT-TYPE
			SYNTAX	INTEGER
			MAX-ACCESS	read-only
			STATUS	current
			::= { hmWanMbus4F 90 }

hmWanMbus4FValue2A		OBJECT-TYPE
			SYNTAX	INTEGER
			MAX-ACCESS	read-only
			STATUS	current
			::= { hmWanMbus4F 91 }

hmWanMbus4FVIF2B		OBJECT-TYPE
			SYNTAX	INTEGER
			MAX-ACCESS	read-only
			STATUS	current
			::= { hmWanMbus4F 92 }

hmWanMbus4FValue2B		OBJECT-TYPE
			SYNTAX	INTEGER
			MAX-ACCESS	read-only
			STATUS	current
			::= { hmWanMbus4F 93 }

hmWanMbus4FVIF2C		OBJECT-TYPE
			SYNTAX	INTEGER
			MAX-ACCESS	read-only
			STATUS	current
			::= { hmWanMbus4F 94 }

hmWanMbus4FValue2C		OBJECT-TYPE
			SYNTAX	INTEGER
			MAX-ACCESS	read-only
			STATUS	current
			::= { hmWanMbus4F 95 }

hmWanMbus4FVIF2D		OBJECT-TYPE
			SYNTAX	INTEGER
			MAX-ACCESS	read-only
			STATUS	current
			::= { hmWanMbus4F 96 }

hmWanMbus4FValue2D		OBJECT-TYPE
			SYNTAX	INTEGER
			MAX-ACCESS	read-only
			STATUS	current
			::= { hmWanMbus4F 97 }

hmWanMbus4FVIF2E		OBJECT-TYPE
			SYNTAX	INTEGER
			MAX-ACCESS	read-only
			STATUS	current
			::= { hmWanMbus4F 98 }

hmWanMbus4FValue2E		OBJECT-TYPE
			SYNTAX	INTEGER
			MAX-ACCESS	read-only
			STATUS	current
			::= { hmWanMbus4F 99 }

hmWanMbus4FVIF2F		OBJECT-TYPE
			SYNTAX	INTEGER
			MAX-ACCESS	read-only
			STATUS	current
			::= { hmWanMbus4F 100 }

hmWanMbus4FValue2F		OBJECT-TYPE
			SYNTAX	INTEGER
			MAX-ACCESS	read-only
			STATUS	current
			::= { hmWanMbus4F 101 }

hmWanMbus50			OBJECT IDENTIFIER ::= { hmWanMbus 80 }

hmWanMbus50IdNumber		OBJECT-TYPE
			SYNTAX	Gauge32
			MAX-ACCESS	read-only
			STATUS	current
			::= { hmWanMbus50 1 }

hmWanMbus50Manufacturer	OBJECT-TYPE
			SYNTAX	Gauge32
			MAX-ACCESS	read-only
			STATUS	current
			::= { hmWanMbus50 2 }

hmWanMbus50Version		OBJECT-TYPE
			SYNTAX	Gauge32
			MAX-ACCESS	read-only
			STATUS	current
			::= { hmWanMbus50 3 }

hmWanMbus50Medium		OBJECT-TYPE
			SYNTAX	Gauge32
			MAX-ACCESS	read-only
			STATUS	current
			::= { hmWanMbus50 4 }

hmWanMbus50Status		OBJECT-TYPE
			SYNTAX	Gauge32
			MAX-ACCESS	read-only
			STATUS	current
			::= { hmWanMbus50 5 }

hmWanMbus50VIF00		OBJECT-TYPE
			SYNTAX	INTEGER
			MAX-ACCESS	read-only
			STATUS	current
			::= { hmWanMbus50 6 }

hmWanMbus50Value00		OBJECT-TYPE
			SYNTAX	INTEGER
			MAX-ACCESS	read-only
			STATUS	current
			::= { hmWanMbus50 7 }

hmWanMbus50VIF01		OBJECT-TYPE
			SYNTAX	INTEGER
			MAX-ACCESS	read-only
			STATUS	current
			::= { hmWanMbus50 8 }

hmWanMbus50Value01		OBJECT-TYPE
			SYNTAX	INTEGER
			MAX-ACCESS	read-only
			STATUS	current
			::= { hmWanMbus50 9 }

hmWanMbus50VIF02		OBJECT-TYPE
			SYNTAX	INTEGER
			MAX-ACCESS	read-only
			STATUS	current
			::= { hmWanMbus50 10 }

hmWanMbus50Value02		OBJECT-TYPE
			SYNTAX	INTEGER
			MAX-ACCESS	read-only
			STATUS	current
			::= { hmWanMbus50 11 }

hmWanMbus50VIF03		OBJECT-TYPE
			SYNTAX	INTEGER
			MAX-ACCESS	read-only
			STATUS	current
			::= { hmWanMbus50 12 }

hmWanMbus50Value03		OBJECT-TYPE
			SYNTAX	INTEGER
			MAX-ACCESS	read-only
			STATUS	current
			::= { hmWanMbus50 13 }

hmWanMbus50VIF04		OBJECT-TYPE
			SYNTAX	INTEGER
			MAX-ACCESS	read-only
			STATUS	current
			::= { hmWanMbus50 14 }

hmWanMbus50Value04		OBJECT-TYPE
			SYNTAX	INTEGER
			MAX-ACCESS	read-only
			STATUS	current
			::= { hmWanMbus50 15 }

hmWanMbus50VIF05		OBJECT-TYPE
			SYNTAX	INTEGER
			MAX-ACCESS	read-only
			STATUS	current
			::= { hmWanMbus50 16 }

hmWanMbus50Value05		OBJECT-TYPE
			SYNTAX	INTEGER
			MAX-ACCESS	read-only
			STATUS	current
			::= { hmWanMbus50 17 }

hmWanMbus50VIF06		OBJECT-TYPE
			SYNTAX	INTEGER
			MAX-ACCESS	read-only
			STATUS	current
			::= { hmWanMbus50 18 }

hmWanMbus50Value06		OBJECT-TYPE
			SYNTAX	INTEGER
			MAX-ACCESS	read-only
			STATUS	current
			::= { hmWanMbus50 19 }

hmWanMbus50VIF07		OBJECT-TYPE
			SYNTAX	INTEGER
			MAX-ACCESS	read-only
			STATUS	current
			::= { hmWanMbus50 20 }

hmWanMbus50Value07		OBJECT-TYPE
			SYNTAX	INTEGER
			MAX-ACCESS	read-only
			STATUS	current
			::= { hmWanMbus50 21 }

hmWanMbus50VIF08		OBJECT-TYPE
			SYNTAX	INTEGER
			MAX-ACCESS	read-only
			STATUS	current
			::= { hmWanMbus50 22 }

hmWanMbus50Value08		OBJECT-TYPE
			SYNTAX	INTEGER
			MAX-ACCESS	read-only
			STATUS	current
			::= { hmWanMbus50 23 }

hmWanMbus50VIF09		OBJECT-TYPE
			SYNTAX	INTEGER
			MAX-ACCESS	read-only
			STATUS	current
			::= { hmWanMbus50 24 }

hmWanMbus50Value09		OBJECT-TYPE
			SYNTAX	INTEGER
			MAX-ACCESS	read-only
			STATUS	current
			::= { hmWanMbus50 25 }

hmWanMbus50VIF0A		OBJECT-TYPE
			SYNTAX	INTEGER
			MAX-ACCESS	read-only
			STATUS	current
			::= { hmWanMbus50 26 }

hmWanMbus50Value0A		OBJECT-TYPE
			SYNTAX	INTEGER
			MAX-ACCESS	read-only
			STATUS	current
			::= { hmWanMbus50 27 }

hmWanMbus50VIF0B		OBJECT-TYPE
			SYNTAX	INTEGER
			MAX-ACCESS	read-only
			STATUS	current
			::= { hmWanMbus50 28 }

hmWanMbus50Value0B		OBJECT-TYPE
			SYNTAX	INTEGER
			MAX-ACCESS	read-only
			STATUS	current
			::= { hmWanMbus50 29 }

hmWanMbus50VIF0C		OBJECT-TYPE
			SYNTAX	INTEGER
			MAX-ACCESS	read-only
			STATUS	current
			::= { hmWanMbus50 30 }

hmWanMbus50Value0C		OBJECT-TYPE
			SYNTAX	INTEGER
			MAX-ACCESS	read-only
			STATUS	current
			::= { hmWanMbus50 31 }

hmWanMbus50VIF0D		OBJECT-TYPE
			SYNTAX	INTEGER
			MAX-ACCESS	read-only
			STATUS	current
			::= { hmWanMbus50 32 }

hmWanMbus50Value0D		OBJECT-TYPE
			SYNTAX	INTEGER
			MAX-ACCESS	read-only
			STATUS	current
			::= { hmWanMbus50 33 }

hmWanMbus50VIF0E		OBJECT-TYPE
			SYNTAX	INTEGER
			MAX-ACCESS	read-only
			STATUS	current
			::= { hmWanMbus50 34 }

hmWanMbus50Value0E		OBJECT-TYPE
			SYNTAX	INTEGER
			MAX-ACCESS	read-only
			STATUS	current
			::= { hmWanMbus50 35 }

hmWanMbus50VIF0F		OBJECT-TYPE
			SYNTAX	INTEGER
			MAX-ACCESS	read-only
			STATUS	current
			::= { hmWanMbus50 36 }

hmWanMbus50Value0F		OBJECT-TYPE
			SYNTAX	INTEGER
			MAX-ACCESS	read-only
			STATUS	current
			::= { hmWanMbus50 37 }

hmWanMbus50VIF10		OBJECT-TYPE
			SYNTAX	INTEGER
			MAX-ACCESS	read-only
			STATUS	current
			::= { hmWanMbus50 38 }

hmWanMbus50Value10		OBJECT-TYPE
			SYNTAX	INTEGER
			MAX-ACCESS	read-only
			STATUS	current
			::= { hmWanMbus50 39 }

hmWanMbus50VIF11		OBJECT-TYPE
			SYNTAX	INTEGER
			MAX-ACCESS	read-only
			STATUS	current
			::= { hmWanMbus50 40 }

hmWanMbus50Value11		OBJECT-TYPE
			SYNTAX	INTEGER
			MAX-ACCESS	read-only
			STATUS	current
			::= { hmWanMbus50 41 }

hmWanMbus50VIF12		OBJECT-TYPE
			SYNTAX	INTEGER
			MAX-ACCESS	read-only
			STATUS	current
			::= { hmWanMbus50 42 }

hmWanMbus50Value12		OBJECT-TYPE
			SYNTAX	INTEGER
			MAX-ACCESS	read-only
			STATUS	current
			::= { hmWanMbus50 43 }

hmWanMbus50VIF13		OBJECT-TYPE
			SYNTAX	INTEGER
			MAX-ACCESS	read-only
			STATUS	current
			::= { hmWanMbus50 44 }

hmWanMbus50Value13		OBJECT-TYPE
			SYNTAX	INTEGER
			MAX-ACCESS	read-only
			STATUS	current
			::= { hmWanMbus50 45 }

hmWanMbus50VIF14		OBJECT-TYPE
			SYNTAX	INTEGER
			MAX-ACCESS	read-only
			STATUS	current
			::= { hmWanMbus50 46 }

hmWanMbus50Value14		OBJECT-TYPE
			SYNTAX	INTEGER
			MAX-ACCESS	read-only
			STATUS	current
			::= { hmWanMbus50 47 }

hmWanMbus50VIF15		OBJECT-TYPE
			SYNTAX	INTEGER
			MAX-ACCESS	read-only
			STATUS	current
			::= { hmWanMbus50 48 }

hmWanMbus50Value15		OBJECT-TYPE
			SYNTAX	INTEGER
			MAX-ACCESS	read-only
			STATUS	current
			::= { hmWanMbus50 49 }

hmWanMbus50VIF16		OBJECT-TYPE
			SYNTAX	INTEGER
			MAX-ACCESS	read-only
			STATUS	current
			::= { hmWanMbus50 50 }

hmWanMbus50Value16		OBJECT-TYPE
			SYNTAX	INTEGER
			MAX-ACCESS	read-only
			STATUS	current
			::= { hmWanMbus50 51 }

hmWanMbus50VIF17		OBJECT-TYPE
			SYNTAX	INTEGER
			MAX-ACCESS	read-only
			STATUS	current
			::= { hmWanMbus50 52 }

hmWanMbus50Value17		OBJECT-TYPE
			SYNTAX	INTEGER
			MAX-ACCESS	read-only
			STATUS	current
			::= { hmWanMbus50 53 }

hmWanMbus50VIF18		OBJECT-TYPE
			SYNTAX	INTEGER
			MAX-ACCESS	read-only
			STATUS	current
			::= { hmWanMbus50 54 }

hmWanMbus50Value18		OBJECT-TYPE
			SYNTAX	INTEGER
			MAX-ACCESS	read-only
			STATUS	current
			::= { hmWanMbus50 55 }

hmWanMbus50VIF19		OBJECT-TYPE
			SYNTAX	INTEGER
			MAX-ACCESS	read-only
			STATUS	current
			::= { hmWanMbus50 56 }

hmWanMbus50Value19		OBJECT-TYPE
			SYNTAX	INTEGER
			MAX-ACCESS	read-only
			STATUS	current
			::= { hmWanMbus50 57 }

hmWanMbus50VIF1A		OBJECT-TYPE
			SYNTAX	INTEGER
			MAX-ACCESS	read-only
			STATUS	current
			::= { hmWanMbus50 58 }

hmWanMbus50Value1A		OBJECT-TYPE
			SYNTAX	INTEGER
			MAX-ACCESS	read-only
			STATUS	current
			::= { hmWanMbus50 59 }

hmWanMbus50VIF1B		OBJECT-TYPE
			SYNTAX	INTEGER
			MAX-ACCESS	read-only
			STATUS	current
			::= { hmWanMbus50 60 }

hmWanMbus50Value1B		OBJECT-TYPE
			SYNTAX	INTEGER
			MAX-ACCESS	read-only
			STATUS	current
			::= { hmWanMbus50 61 }

hmWanMbus50VIF1C		OBJECT-TYPE
			SYNTAX	INTEGER
			MAX-ACCESS	read-only
			STATUS	current
			::= { hmWanMbus50 62 }

hmWanMbus50Value1C		OBJECT-TYPE
			SYNTAX	INTEGER
			MAX-ACCESS	read-only
			STATUS	current
			::= { hmWanMbus50 63 }

hmWanMbus50VIF1D		OBJECT-TYPE
			SYNTAX	INTEGER
			MAX-ACCESS	read-only
			STATUS	current
			::= { hmWanMbus50 64 }

hmWanMbus50Value1D		OBJECT-TYPE
			SYNTAX	INTEGER
			MAX-ACCESS	read-only
			STATUS	current
			::= { hmWanMbus50 65 }

hmWanMbus50VIF1E		OBJECT-TYPE
			SYNTAX	INTEGER
			MAX-ACCESS	read-only
			STATUS	current
			::= { hmWanMbus50 66 }

hmWanMbus50Value1E		OBJECT-TYPE
			SYNTAX	INTEGER
			MAX-ACCESS	read-only
			STATUS	current
			::= { hmWanMbus50 67 }

hmWanMbus50VIF1F		OBJECT-TYPE
			SYNTAX	INTEGER
			MAX-ACCESS	read-only
			STATUS	current
			::= { hmWanMbus50 68 }

hmWanMbus50Value1F		OBJECT-TYPE
			SYNTAX	INTEGER
			MAX-ACCESS	read-only
			STATUS	current
			::= { hmWanMbus50 69 }

hmWanMbus50VIF20		OBJECT-TYPE
			SYNTAX	INTEGER
			MAX-ACCESS	read-only
			STATUS	current
			::= { hmWanMbus50 70 }

hmWanMbus50Value20		OBJECT-TYPE
			SYNTAX	INTEGER
			MAX-ACCESS	read-only
			STATUS	current
			::= { hmWanMbus50 71 }

hmWanMbus50VIF21		OBJECT-TYPE
			SYNTAX	INTEGER
			MAX-ACCESS	read-only
			STATUS	current
			::= { hmWanMbus50 72 }

hmWanMbus50Value21		OBJECT-TYPE
			SYNTAX	INTEGER
			MAX-ACCESS	read-only
			STATUS	current
			::= { hmWanMbus50 73 }

hmWanMbus50VIF22		OBJECT-TYPE
			SYNTAX	INTEGER
			MAX-ACCESS	read-only
			STATUS	current
			::= { hmWanMbus50 74 }

hmWanMbus50Value22		OBJECT-TYPE
			SYNTAX	INTEGER
			MAX-ACCESS	read-only
			STATUS	current
			::= { hmWanMbus50 75 }

hmWanMbus50VIF23		OBJECT-TYPE
			SYNTAX	INTEGER
			MAX-ACCESS	read-only
			STATUS	current
			::= { hmWanMbus50 76 }

hmWanMbus50Value23		OBJECT-TYPE
			SYNTAX	INTEGER
			MAX-ACCESS	read-only
			STATUS	current
			::= { hmWanMbus50 77 }

hmWanMbus50VIF24		OBJECT-TYPE
			SYNTAX	INTEGER
			MAX-ACCESS	read-only
			STATUS	current
			::= { hmWanMbus50 78 }

hmWanMbus50Value24		OBJECT-TYPE
			SYNTAX	INTEGER
			MAX-ACCESS	read-only
			STATUS	current
			::= { hmWanMbus50 79 }

hmWanMbus50VIF25		OBJECT-TYPE
			SYNTAX	INTEGER
			MAX-ACCESS	read-only
			STATUS	current
			::= { hmWanMbus50 80 }

hmWanMbus50Value25		OBJECT-TYPE
			SYNTAX	INTEGER
			MAX-ACCESS	read-only
			STATUS	current
			::= { hmWanMbus50 81 }

hmWanMbus50VIF26		OBJECT-TYPE
			SYNTAX	INTEGER
			MAX-ACCESS	read-only
			STATUS	current
			::= { hmWanMbus50 82 }

hmWanMbus50Value26		OBJECT-TYPE
			SYNTAX	INTEGER
			MAX-ACCESS	read-only
			STATUS	current
			::= { hmWanMbus50 83 }

hmWanMbus50VIF27		OBJECT-TYPE
			SYNTAX	INTEGER
			MAX-ACCESS	read-only
			STATUS	current
			::= { hmWanMbus50 84 }

hmWanMbus50Value27		OBJECT-TYPE
			SYNTAX	INTEGER
			MAX-ACCESS	read-only
			STATUS	current
			::= { hmWanMbus50 85 }

hmWanMbus50VIF28		OBJECT-TYPE
			SYNTAX	INTEGER
			MAX-ACCESS	read-only
			STATUS	current
			::= { hmWanMbus50 86 }

hmWanMbus50Value28		OBJECT-TYPE
			SYNTAX	INTEGER
			MAX-ACCESS	read-only
			STATUS	current
			::= { hmWanMbus50 87 }

hmWanMbus50VIF29		OBJECT-TYPE
			SYNTAX	INTEGER
			MAX-ACCESS	read-only
			STATUS	current
			::= { hmWanMbus50 88 }

hmWanMbus50Value29		OBJECT-TYPE
			SYNTAX	INTEGER
			MAX-ACCESS	read-only
			STATUS	current
			::= { hmWanMbus50 89 }

hmWanMbus50VIF2A		OBJECT-TYPE
			SYNTAX	INTEGER
			MAX-ACCESS	read-only
			STATUS	current
			::= { hmWanMbus50 90 }

hmWanMbus50Value2A		OBJECT-TYPE
			SYNTAX	INTEGER
			MAX-ACCESS	read-only
			STATUS	current
			::= { hmWanMbus50 91 }

hmWanMbus50VIF2B		OBJECT-TYPE
			SYNTAX	INTEGER
			MAX-ACCESS	read-only
			STATUS	current
			::= { hmWanMbus50 92 }

hmWanMbus50Value2B		OBJECT-TYPE
			SYNTAX	INTEGER
			MAX-ACCESS	read-only
			STATUS	current
			::= { hmWanMbus50 93 }

hmWanMbus50VIF2C		OBJECT-TYPE
			SYNTAX	INTEGER
			MAX-ACCESS	read-only
			STATUS	current
			::= { hmWanMbus50 94 }

hmWanMbus50Value2C		OBJECT-TYPE
			SYNTAX	INTEGER
			MAX-ACCESS	read-only
			STATUS	current
			::= { hmWanMbus50 95 }

hmWanMbus50VIF2D		OBJECT-TYPE
			SYNTAX	INTEGER
			MAX-ACCESS	read-only
			STATUS	current
			::= { hmWanMbus50 96 }

hmWanMbus50Value2D		OBJECT-TYPE
			SYNTAX	INTEGER
			MAX-ACCESS	read-only
			STATUS	current
			::= { hmWanMbus50 97 }

hmWanMbus50VIF2E		OBJECT-TYPE
			SYNTAX	INTEGER
			MAX-ACCESS	read-only
			STATUS	current
			::= { hmWanMbus50 98 }

hmWanMbus50Value2E		OBJECT-TYPE
			SYNTAX	INTEGER
			MAX-ACCESS	read-only
			STATUS	current
			::= { hmWanMbus50 99 }

hmWanMbus50VIF2F		OBJECT-TYPE
			SYNTAX	INTEGER
			MAX-ACCESS	read-only
			STATUS	current
			::= { hmWanMbus50 100 }

hmWanMbus50Value2F		OBJECT-TYPE
			SYNTAX	INTEGER
			MAX-ACCESS	read-only
			STATUS	current
			::= { hmWanMbus50 101 }

hmWanMbus51			OBJECT IDENTIFIER ::= { hmWanMbus 81 }

hmWanMbus51IdNumber		OBJECT-TYPE
			SYNTAX	Gauge32
			MAX-ACCESS	read-only
			STATUS	current
			::= { hmWanMbus51 1 }

hmWanMbus51Manufacturer	OBJECT-TYPE
			SYNTAX	Gauge32
			MAX-ACCESS	read-only
			STATUS	current
			::= { hmWanMbus51 2 }

hmWanMbus51Version		OBJECT-TYPE
			SYNTAX	Gauge32
			MAX-ACCESS	read-only
			STATUS	current
			::= { hmWanMbus51 3 }

hmWanMbus51Medium		OBJECT-TYPE
			SYNTAX	Gauge32
			MAX-ACCESS	read-only
			STATUS	current
			::= { hmWanMbus51 4 }

hmWanMbus51Status		OBJECT-TYPE
			SYNTAX	Gauge32
			MAX-ACCESS	read-only
			STATUS	current
			::= { hmWanMbus51 5 }

hmWanMbus51VIF00		OBJECT-TYPE
			SYNTAX	INTEGER
			MAX-ACCESS	read-only
			STATUS	current
			::= { hmWanMbus51 6 }

hmWanMbus51Value00		OBJECT-TYPE
			SYNTAX	INTEGER
			MAX-ACCESS	read-only
			STATUS	current
			::= { hmWanMbus51 7 }

hmWanMbus51VIF01		OBJECT-TYPE
			SYNTAX	INTEGER
			MAX-ACCESS	read-only
			STATUS	current
			::= { hmWanMbus51 8 }

hmWanMbus51Value01		OBJECT-TYPE
			SYNTAX	INTEGER
			MAX-ACCESS	read-only
			STATUS	current
			::= { hmWanMbus51 9 }

hmWanMbus51VIF02		OBJECT-TYPE
			SYNTAX	INTEGER
			MAX-ACCESS	read-only
			STATUS	current
			::= { hmWanMbus51 10 }

hmWanMbus51Value02		OBJECT-TYPE
			SYNTAX	INTEGER
			MAX-ACCESS	read-only
			STATUS	current
			::= { hmWanMbus51 11 }

hmWanMbus51VIF03		OBJECT-TYPE
			SYNTAX	INTEGER
			MAX-ACCESS	read-only
			STATUS	current
			::= { hmWanMbus51 12 }

hmWanMbus51Value03		OBJECT-TYPE
			SYNTAX	INTEGER
			MAX-ACCESS	read-only
			STATUS	current
			::= { hmWanMbus51 13 }

hmWanMbus51VIF04		OBJECT-TYPE
			SYNTAX	INTEGER
			MAX-ACCESS	read-only
			STATUS	current
			::= { hmWanMbus51 14 }

hmWanMbus51Value04		OBJECT-TYPE
			SYNTAX	INTEGER
			MAX-ACCESS	read-only
			STATUS	current
			::= { hmWanMbus51 15 }

hmWanMbus51VIF05		OBJECT-TYPE
			SYNTAX	INTEGER
			MAX-ACCESS	read-only
			STATUS	current
			::= { hmWanMbus51 16 }

hmWanMbus51Value05		OBJECT-TYPE
			SYNTAX	INTEGER
			MAX-ACCESS	read-only
			STATUS	current
			::= { hmWanMbus51 17 }

hmWanMbus51VIF06		OBJECT-TYPE
			SYNTAX	INTEGER
			MAX-ACCESS	read-only
			STATUS	current
			::= { hmWanMbus51 18 }

hmWanMbus51Value06		OBJECT-TYPE
			SYNTAX	INTEGER
			MAX-ACCESS	read-only
			STATUS	current
			::= { hmWanMbus51 19 }

hmWanMbus51VIF07		OBJECT-TYPE
			SYNTAX	INTEGER
			MAX-ACCESS	read-only
			STATUS	current
			::= { hmWanMbus51 20 }

hmWanMbus51Value07		OBJECT-TYPE
			SYNTAX	INTEGER
			MAX-ACCESS	read-only
			STATUS	current
			::= { hmWanMbus51 21 }

hmWanMbus51VIF08		OBJECT-TYPE
			SYNTAX	INTEGER
			MAX-ACCESS	read-only
			STATUS	current
			::= { hmWanMbus51 22 }

hmWanMbus51Value08		OBJECT-TYPE
			SYNTAX	INTEGER
			MAX-ACCESS	read-only
			STATUS	current
			::= { hmWanMbus51 23 }

hmWanMbus51VIF09		OBJECT-TYPE
			SYNTAX	INTEGER
			MAX-ACCESS	read-only
			STATUS	current
			::= { hmWanMbus51 24 }

hmWanMbus51Value09		OBJECT-TYPE
			SYNTAX	INTEGER
			MAX-ACCESS	read-only
			STATUS	current
			::= { hmWanMbus51 25 }

hmWanMbus51VIF0A		OBJECT-TYPE
			SYNTAX	INTEGER
			MAX-ACCESS	read-only
			STATUS	current
			::= { hmWanMbus51 26 }

hmWanMbus51Value0A		OBJECT-TYPE
			SYNTAX	INTEGER
			MAX-ACCESS	read-only
			STATUS	current
			::= { hmWanMbus51 27 }

hmWanMbus51VIF0B		OBJECT-TYPE
			SYNTAX	INTEGER
			MAX-ACCESS	read-only
			STATUS	current
			::= { hmWanMbus51 28 }

hmWanMbus51Value0B		OBJECT-TYPE
			SYNTAX	INTEGER
			MAX-ACCESS	read-only
			STATUS	current
			::= { hmWanMbus51 29 }

hmWanMbus51VIF0C		OBJECT-TYPE
			SYNTAX	INTEGER
			MAX-ACCESS	read-only
			STATUS	current
			::= { hmWanMbus51 30 }

hmWanMbus51Value0C		OBJECT-TYPE
			SYNTAX	INTEGER
			MAX-ACCESS	read-only
			STATUS	current
			::= { hmWanMbus51 31 }

hmWanMbus51VIF0D		OBJECT-TYPE
			SYNTAX	INTEGER
			MAX-ACCESS	read-only
			STATUS	current
			::= { hmWanMbus51 32 }

hmWanMbus51Value0D		OBJECT-TYPE
			SYNTAX	INTEGER
			MAX-ACCESS	read-only
			STATUS	current
			::= { hmWanMbus51 33 }

hmWanMbus51VIF0E		OBJECT-TYPE
			SYNTAX	INTEGER
			MAX-ACCESS	read-only
			STATUS	current
			::= { hmWanMbus51 34 }

hmWanMbus51Value0E		OBJECT-TYPE
			SYNTAX	INTEGER
			MAX-ACCESS	read-only
			STATUS	current
			::= { hmWanMbus51 35 }

hmWanMbus51VIF0F		OBJECT-TYPE
			SYNTAX	INTEGER
			MAX-ACCESS	read-only
			STATUS	current
			::= { hmWanMbus51 36 }

hmWanMbus51Value0F		OBJECT-TYPE
			SYNTAX	INTEGER
			MAX-ACCESS	read-only
			STATUS	current
			::= { hmWanMbus51 37 }

hmWanMbus51VIF10		OBJECT-TYPE
			SYNTAX	INTEGER
			MAX-ACCESS	read-only
			STATUS	current
			::= { hmWanMbus51 38 }

hmWanMbus51Value10		OBJECT-TYPE
			SYNTAX	INTEGER
			MAX-ACCESS	read-only
			STATUS	current
			::= { hmWanMbus51 39 }

hmWanMbus51VIF11		OBJECT-TYPE
			SYNTAX	INTEGER
			MAX-ACCESS	read-only
			STATUS	current
			::= { hmWanMbus51 40 }

hmWanMbus51Value11		OBJECT-TYPE
			SYNTAX	INTEGER
			MAX-ACCESS	read-only
			STATUS	current
			::= { hmWanMbus51 41 }

hmWanMbus51VIF12		OBJECT-TYPE
			SYNTAX	INTEGER
			MAX-ACCESS	read-only
			STATUS	current
			::= { hmWanMbus51 42 }

hmWanMbus51Value12		OBJECT-TYPE
			SYNTAX	INTEGER
			MAX-ACCESS	read-only
			STATUS	current
			::= { hmWanMbus51 43 }

hmWanMbus51VIF13		OBJECT-TYPE
			SYNTAX	INTEGER
			MAX-ACCESS	read-only
			STATUS	current
			::= { hmWanMbus51 44 }

hmWanMbus51Value13		OBJECT-TYPE
			SYNTAX	INTEGER
			MAX-ACCESS	read-only
			STATUS	current
			::= { hmWanMbus51 45 }

hmWanMbus51VIF14		OBJECT-TYPE
			SYNTAX	INTEGER
			MAX-ACCESS	read-only
			STATUS	current
			::= { hmWanMbus51 46 }

hmWanMbus51Value14		OBJECT-TYPE
			SYNTAX	INTEGER
			MAX-ACCESS	read-only
			STATUS	current
			::= { hmWanMbus51 47 }

hmWanMbus51VIF15		OBJECT-TYPE
			SYNTAX	INTEGER
			MAX-ACCESS	read-only
			STATUS	current
			::= { hmWanMbus51 48 }

hmWanMbus51Value15		OBJECT-TYPE
			SYNTAX	INTEGER
			MAX-ACCESS	read-only
			STATUS	current
			::= { hmWanMbus51 49 }

hmWanMbus51VIF16		OBJECT-TYPE
			SYNTAX	INTEGER
			MAX-ACCESS	read-only
			STATUS	current
			::= { hmWanMbus51 50 }

hmWanMbus51Value16		OBJECT-TYPE
			SYNTAX	INTEGER
			MAX-ACCESS	read-only
			STATUS	current
			::= { hmWanMbus51 51 }

hmWanMbus51VIF17		OBJECT-TYPE
			SYNTAX	INTEGER
			MAX-ACCESS	read-only
			STATUS	current
			::= { hmWanMbus51 52 }

hmWanMbus51Value17		OBJECT-TYPE
			SYNTAX	INTEGER
			MAX-ACCESS	read-only
			STATUS	current
			::= { hmWanMbus51 53 }

hmWanMbus51VIF18		OBJECT-TYPE
			SYNTAX	INTEGER
			MAX-ACCESS	read-only
			STATUS	current
			::= { hmWanMbus51 54 }

hmWanMbus51Value18		OBJECT-TYPE
			SYNTAX	INTEGER
			MAX-ACCESS	read-only
			STATUS	current
			::= { hmWanMbus51 55 }

hmWanMbus51VIF19		OBJECT-TYPE
			SYNTAX	INTEGER
			MAX-ACCESS	read-only
			STATUS	current
			::= { hmWanMbus51 56 }

hmWanMbus51Value19		OBJECT-TYPE
			SYNTAX	INTEGER
			MAX-ACCESS	read-only
			STATUS	current
			::= { hmWanMbus51 57 }

hmWanMbus51VIF1A		OBJECT-TYPE
			SYNTAX	INTEGER
			MAX-ACCESS	read-only
			STATUS	current
			::= { hmWanMbus51 58 }

hmWanMbus51Value1A		OBJECT-TYPE
			SYNTAX	INTEGER
			MAX-ACCESS	read-only
			STATUS	current
			::= { hmWanMbus51 59 }

hmWanMbus51VIF1B		OBJECT-TYPE
			SYNTAX	INTEGER
			MAX-ACCESS	read-only
			STATUS	current
			::= { hmWanMbus51 60 }

hmWanMbus51Value1B		OBJECT-TYPE
			SYNTAX	INTEGER
			MAX-ACCESS	read-only
			STATUS	current
			::= { hmWanMbus51 61 }

hmWanMbus51VIF1C		OBJECT-TYPE
			SYNTAX	INTEGER
			MAX-ACCESS	read-only
			STATUS	current
			::= { hmWanMbus51 62 }

hmWanMbus51Value1C		OBJECT-TYPE
			SYNTAX	INTEGER
			MAX-ACCESS	read-only
			STATUS	current
			::= { hmWanMbus51 63 }

hmWanMbus51VIF1D		OBJECT-TYPE
			SYNTAX	INTEGER
			MAX-ACCESS	read-only
			STATUS	current
			::= { hmWanMbus51 64 }

hmWanMbus51Value1D		OBJECT-TYPE
			SYNTAX	INTEGER
			MAX-ACCESS	read-only
			STATUS	current
			::= { hmWanMbus51 65 }

hmWanMbus51VIF1E		OBJECT-TYPE
			SYNTAX	INTEGER
			MAX-ACCESS	read-only
			STATUS	current
			::= { hmWanMbus51 66 }

hmWanMbus51Value1E		OBJECT-TYPE
			SYNTAX	INTEGER
			MAX-ACCESS	read-only
			STATUS	current
			::= { hmWanMbus51 67 }

hmWanMbus51VIF1F		OBJECT-TYPE
			SYNTAX	INTEGER
			MAX-ACCESS	read-only
			STATUS	current
			::= { hmWanMbus51 68 }

hmWanMbus51Value1F		OBJECT-TYPE
			SYNTAX	INTEGER
			MAX-ACCESS	read-only
			STATUS	current
			::= { hmWanMbus51 69 }

hmWanMbus51VIF20		OBJECT-TYPE
			SYNTAX	INTEGER
			MAX-ACCESS	read-only
			STATUS	current
			::= { hmWanMbus51 70 }

hmWanMbus51Value20		OBJECT-TYPE
			SYNTAX	INTEGER
			MAX-ACCESS	read-only
			STATUS	current
			::= { hmWanMbus51 71 }

hmWanMbus51VIF21		OBJECT-TYPE
			SYNTAX	INTEGER
			MAX-ACCESS	read-only
			STATUS	current
			::= { hmWanMbus51 72 }

hmWanMbus51Value21		OBJECT-TYPE
			SYNTAX	INTEGER
			MAX-ACCESS	read-only
			STATUS	current
			::= { hmWanMbus51 73 }

hmWanMbus51VIF22		OBJECT-TYPE
			SYNTAX	INTEGER
			MAX-ACCESS	read-only
			STATUS	current
			::= { hmWanMbus51 74 }

hmWanMbus51Value22		OBJECT-TYPE
			SYNTAX	INTEGER
			MAX-ACCESS	read-only
			STATUS	current
			::= { hmWanMbus51 75 }

hmWanMbus51VIF23		OBJECT-TYPE
			SYNTAX	INTEGER
			MAX-ACCESS	read-only
			STATUS	current
			::= { hmWanMbus51 76 }

hmWanMbus51Value23		OBJECT-TYPE
			SYNTAX	INTEGER
			MAX-ACCESS	read-only
			STATUS	current
			::= { hmWanMbus51 77 }

hmWanMbus51VIF24		OBJECT-TYPE
			SYNTAX	INTEGER
			MAX-ACCESS	read-only
			STATUS	current
			::= { hmWanMbus51 78 }

hmWanMbus51Value24		OBJECT-TYPE
			SYNTAX	INTEGER
			MAX-ACCESS	read-only
			STATUS	current
			::= { hmWanMbus51 79 }

hmWanMbus51VIF25		OBJECT-TYPE
			SYNTAX	INTEGER
			MAX-ACCESS	read-only
			STATUS	current
			::= { hmWanMbus51 80 }

hmWanMbus51Value25		OBJECT-TYPE
			SYNTAX	INTEGER
			MAX-ACCESS	read-only
			STATUS	current
			::= { hmWanMbus51 81 }

hmWanMbus51VIF26		OBJECT-TYPE
			SYNTAX	INTEGER
			MAX-ACCESS	read-only
			STATUS	current
			::= { hmWanMbus51 82 }

hmWanMbus51Value26		OBJECT-TYPE
			SYNTAX	INTEGER
			MAX-ACCESS	read-only
			STATUS	current
			::= { hmWanMbus51 83 }

hmWanMbus51VIF27		OBJECT-TYPE
			SYNTAX	INTEGER
			MAX-ACCESS	read-only
			STATUS	current
			::= { hmWanMbus51 84 }

hmWanMbus51Value27		OBJECT-TYPE
			SYNTAX	INTEGER
			MAX-ACCESS	read-only
			STATUS	current
			::= { hmWanMbus51 85 }

hmWanMbus51VIF28		OBJECT-TYPE
			SYNTAX	INTEGER
			MAX-ACCESS	read-only
			STATUS	current
			::= { hmWanMbus51 86 }

hmWanMbus51Value28		OBJECT-TYPE
			SYNTAX	INTEGER
			MAX-ACCESS	read-only
			STATUS	current
			::= { hmWanMbus51 87 }

hmWanMbus51VIF29		OBJECT-TYPE
			SYNTAX	INTEGER
			MAX-ACCESS	read-only
			STATUS	current
			::= { hmWanMbus51 88 }

hmWanMbus51Value29		OBJECT-TYPE
			SYNTAX	INTEGER
			MAX-ACCESS	read-only
			STATUS	current
			::= { hmWanMbus51 89 }

hmWanMbus51VIF2A		OBJECT-TYPE
			SYNTAX	INTEGER
			MAX-ACCESS	read-only
			STATUS	current
			::= { hmWanMbus51 90 }

hmWanMbus51Value2A		OBJECT-TYPE
			SYNTAX	INTEGER
			MAX-ACCESS	read-only
			STATUS	current
			::= { hmWanMbus51 91 }

hmWanMbus51VIF2B		OBJECT-TYPE
			SYNTAX	INTEGER
			MAX-ACCESS	read-only
			STATUS	current
			::= { hmWanMbus51 92 }

hmWanMbus51Value2B		OBJECT-TYPE
			SYNTAX	INTEGER
			MAX-ACCESS	read-only
			STATUS	current
			::= { hmWanMbus51 93 }

hmWanMbus51VIF2C		OBJECT-TYPE
			SYNTAX	INTEGER
			MAX-ACCESS	read-only
			STATUS	current
			::= { hmWanMbus51 94 }

hmWanMbus51Value2C		OBJECT-TYPE
			SYNTAX	INTEGER
			MAX-ACCESS	read-only
			STATUS	current
			::= { hmWanMbus51 95 }

hmWanMbus51VIF2D		OBJECT-TYPE
			SYNTAX	INTEGER
			MAX-ACCESS	read-only
			STATUS	current
			::= { hmWanMbus51 96 }

hmWanMbus51Value2D		OBJECT-TYPE
			SYNTAX	INTEGER
			MAX-ACCESS	read-only
			STATUS	current
			::= { hmWanMbus51 97 }

hmWanMbus51VIF2E		OBJECT-TYPE
			SYNTAX	INTEGER
			MAX-ACCESS	read-only
			STATUS	current
			::= { hmWanMbus51 98 }

hmWanMbus51Value2E		OBJECT-TYPE
			SYNTAX	INTEGER
			MAX-ACCESS	read-only
			STATUS	current
			::= { hmWanMbus51 99 }

hmWanMbus51VIF2F		OBJECT-TYPE
			SYNTAX	INTEGER
			MAX-ACCESS	read-only
			STATUS	current
			::= { hmWanMbus51 100 }

hmWanMbus51Value2F		OBJECT-TYPE
			SYNTAX	INTEGER
			MAX-ACCESS	read-only
			STATUS	current
			::= { hmWanMbus51 101 }

hmWanMbus52			OBJECT IDENTIFIER ::= { hmWanMbus 82 }

hmWanMbus52IdNumber		OBJECT-TYPE
			SYNTAX	Gauge32
			MAX-ACCESS	read-only
			STATUS	current
			::= { hmWanMbus52 1 }

hmWanMbus52Manufacturer	OBJECT-TYPE
			SYNTAX	Gauge32
			MAX-ACCESS	read-only
			STATUS	current
			::= { hmWanMbus52 2 }

hmWanMbus52Version		OBJECT-TYPE
			SYNTAX	Gauge32
			MAX-ACCESS	read-only
			STATUS	current
			::= { hmWanMbus52 3 }

hmWanMbus52Medium		OBJECT-TYPE
			SYNTAX	Gauge32
			MAX-ACCESS	read-only
			STATUS	current
			::= { hmWanMbus52 4 }

hmWanMbus52Status		OBJECT-TYPE
			SYNTAX	Gauge32
			MAX-ACCESS	read-only
			STATUS	current
			::= { hmWanMbus52 5 }

hmWanMbus52VIF00		OBJECT-TYPE
			SYNTAX	INTEGER
			MAX-ACCESS	read-only
			STATUS	current
			::= { hmWanMbus52 6 }

hmWanMbus52Value00		OBJECT-TYPE
			SYNTAX	INTEGER
			MAX-ACCESS	read-only
			STATUS	current
			::= { hmWanMbus52 7 }

hmWanMbus52VIF01		OBJECT-TYPE
			SYNTAX	INTEGER
			MAX-ACCESS	read-only
			STATUS	current
			::= { hmWanMbus52 8 }

hmWanMbus52Value01		OBJECT-TYPE
			SYNTAX	INTEGER
			MAX-ACCESS	read-only
			STATUS	current
			::= { hmWanMbus52 9 }

hmWanMbus52VIF02		OBJECT-TYPE
			SYNTAX	INTEGER
			MAX-ACCESS	read-only
			STATUS	current
			::= { hmWanMbus52 10 }

hmWanMbus52Value02		OBJECT-TYPE
			SYNTAX	INTEGER
			MAX-ACCESS	read-only
			STATUS	current
			::= { hmWanMbus52 11 }

hmWanMbus52VIF03		OBJECT-TYPE
			SYNTAX	INTEGER
			MAX-ACCESS	read-only
			STATUS	current
			::= { hmWanMbus52 12 }

hmWanMbus52Value03		OBJECT-TYPE
			SYNTAX	INTEGER
			MAX-ACCESS	read-only
			STATUS	current
			::= { hmWanMbus52 13 }

hmWanMbus52VIF04		OBJECT-TYPE
			SYNTAX	INTEGER
			MAX-ACCESS	read-only
			STATUS	current
			::= { hmWanMbus52 14 }

hmWanMbus52Value04		OBJECT-TYPE
			SYNTAX	INTEGER
			MAX-ACCESS	read-only
			STATUS	current
			::= { hmWanMbus52 15 }

hmWanMbus52VIF05		OBJECT-TYPE
			SYNTAX	INTEGER
			MAX-ACCESS	read-only
			STATUS	current
			::= { hmWanMbus52 16 }

hmWanMbus52Value05		OBJECT-TYPE
			SYNTAX	INTEGER
			MAX-ACCESS	read-only
			STATUS	current
			::= { hmWanMbus52 17 }

hmWanMbus52VIF06		OBJECT-TYPE
			SYNTAX	INTEGER
			MAX-ACCESS	read-only
			STATUS	current
			::= { hmWanMbus52 18 }

hmWanMbus52Value06		OBJECT-TYPE
			SYNTAX	INTEGER
			MAX-ACCESS	read-only
			STATUS	current
			::= { hmWanMbus52 19 }

hmWanMbus52VIF07		OBJECT-TYPE
			SYNTAX	INTEGER
			MAX-ACCESS	read-only
			STATUS	current
			::= { hmWanMbus52 20 }

hmWanMbus52Value07		OBJECT-TYPE
			SYNTAX	INTEGER
			MAX-ACCESS	read-only
			STATUS	current
			::= { hmWanMbus52 21 }

hmWanMbus52VIF08		OBJECT-TYPE
			SYNTAX	INTEGER
			MAX-ACCESS	read-only
			STATUS	current
			::= { hmWanMbus52 22 }

hmWanMbus52Value08		OBJECT-TYPE
			SYNTAX	INTEGER
			MAX-ACCESS	read-only
			STATUS	current
			::= { hmWanMbus52 23 }

hmWanMbus52VIF09		OBJECT-TYPE
			SYNTAX	INTEGER
			MAX-ACCESS	read-only
			STATUS	current
			::= { hmWanMbus52 24 }

hmWanMbus52Value09		OBJECT-TYPE
			SYNTAX	INTEGER
			MAX-ACCESS	read-only
			STATUS	current
			::= { hmWanMbus52 25 }

hmWanMbus52VIF0A		OBJECT-TYPE
			SYNTAX	INTEGER
			MAX-ACCESS	read-only
			STATUS	current
			::= { hmWanMbus52 26 }

hmWanMbus52Value0A		OBJECT-TYPE
			SYNTAX	INTEGER
			MAX-ACCESS	read-only
			STATUS	current
			::= { hmWanMbus52 27 }

hmWanMbus52VIF0B		OBJECT-TYPE
			SYNTAX	INTEGER
			MAX-ACCESS	read-only
			STATUS	current
			::= { hmWanMbus52 28 }

hmWanMbus52Value0B		OBJECT-TYPE
			SYNTAX	INTEGER
			MAX-ACCESS	read-only
			STATUS	current
			::= { hmWanMbus52 29 }

hmWanMbus52VIF0C		OBJECT-TYPE
			SYNTAX	INTEGER
			MAX-ACCESS	read-only
			STATUS	current
			::= { hmWanMbus52 30 }

hmWanMbus52Value0C		OBJECT-TYPE
			SYNTAX	INTEGER
			MAX-ACCESS	read-only
			STATUS	current
			::= { hmWanMbus52 31 }

hmWanMbus52VIF0D		OBJECT-TYPE
			SYNTAX	INTEGER
			MAX-ACCESS	read-only
			STATUS	current
			::= { hmWanMbus52 32 }

hmWanMbus52Value0D		OBJECT-TYPE
			SYNTAX	INTEGER
			MAX-ACCESS	read-only
			STATUS	current
			::= { hmWanMbus52 33 }

hmWanMbus52VIF0E		OBJECT-TYPE
			SYNTAX	INTEGER
			MAX-ACCESS	read-only
			STATUS	current
			::= { hmWanMbus52 34 }

hmWanMbus52Value0E		OBJECT-TYPE
			SYNTAX	INTEGER
			MAX-ACCESS	read-only
			STATUS	current
			::= { hmWanMbus52 35 }

hmWanMbus52VIF0F		OBJECT-TYPE
			SYNTAX	INTEGER
			MAX-ACCESS	read-only
			STATUS	current
			::= { hmWanMbus52 36 }

hmWanMbus52Value0F		OBJECT-TYPE
			SYNTAX	INTEGER
			MAX-ACCESS	read-only
			STATUS	current
			::= { hmWanMbus52 37 }

hmWanMbus52VIF10		OBJECT-TYPE
			SYNTAX	INTEGER
			MAX-ACCESS	read-only
			STATUS	current
			::= { hmWanMbus52 38 }

hmWanMbus52Value10		OBJECT-TYPE
			SYNTAX	INTEGER
			MAX-ACCESS	read-only
			STATUS	current
			::= { hmWanMbus52 39 }

hmWanMbus52VIF11		OBJECT-TYPE
			SYNTAX	INTEGER
			MAX-ACCESS	read-only
			STATUS	current
			::= { hmWanMbus52 40 }

hmWanMbus52Value11		OBJECT-TYPE
			SYNTAX	INTEGER
			MAX-ACCESS	read-only
			STATUS	current
			::= { hmWanMbus52 41 }

hmWanMbus52VIF12		OBJECT-TYPE
			SYNTAX	INTEGER
			MAX-ACCESS	read-only
			STATUS	current
			::= { hmWanMbus52 42 }

hmWanMbus52Value12		OBJECT-TYPE
			SYNTAX	INTEGER
			MAX-ACCESS	read-only
			STATUS	current
			::= { hmWanMbus52 43 }

hmWanMbus52VIF13		OBJECT-TYPE
			SYNTAX	INTEGER
			MAX-ACCESS	read-only
			STATUS	current
			::= { hmWanMbus52 44 }

hmWanMbus52Value13		OBJECT-TYPE
			SYNTAX	INTEGER
			MAX-ACCESS	read-only
			STATUS	current
			::= { hmWanMbus52 45 }

hmWanMbus52VIF14		OBJECT-TYPE
			SYNTAX	INTEGER
			MAX-ACCESS	read-only
			STATUS	current
			::= { hmWanMbus52 46 }

hmWanMbus52Value14		OBJECT-TYPE
			SYNTAX	INTEGER
			MAX-ACCESS	read-only
			STATUS	current
			::= { hmWanMbus52 47 }

hmWanMbus52VIF15		OBJECT-TYPE
			SYNTAX	INTEGER
			MAX-ACCESS	read-only
			STATUS	current
			::= { hmWanMbus52 48 }

hmWanMbus52Value15		OBJECT-TYPE
			SYNTAX	INTEGER
			MAX-ACCESS	read-only
			STATUS	current
			::= { hmWanMbus52 49 }

hmWanMbus52VIF16		OBJECT-TYPE
			SYNTAX	INTEGER
			MAX-ACCESS	read-only
			STATUS	current
			::= { hmWanMbus52 50 }

hmWanMbus52Value16		OBJECT-TYPE
			SYNTAX	INTEGER
			MAX-ACCESS	read-only
			STATUS	current
			::= { hmWanMbus52 51 }

hmWanMbus52VIF17		OBJECT-TYPE
			SYNTAX	INTEGER
			MAX-ACCESS	read-only
			STATUS	current
			::= { hmWanMbus52 52 }

hmWanMbus52Value17		OBJECT-TYPE
			SYNTAX	INTEGER
			MAX-ACCESS	read-only
			STATUS	current
			::= { hmWanMbus52 53 }

hmWanMbus52VIF18		OBJECT-TYPE
			SYNTAX	INTEGER
			MAX-ACCESS	read-only
			STATUS	current
			::= { hmWanMbus52 54 }

hmWanMbus52Value18		OBJECT-TYPE
			SYNTAX	INTEGER
			MAX-ACCESS	read-only
			STATUS	current
			::= { hmWanMbus52 55 }

hmWanMbus52VIF19		OBJECT-TYPE
			SYNTAX	INTEGER
			MAX-ACCESS	read-only
			STATUS	current
			::= { hmWanMbus52 56 }

hmWanMbus52Value19		OBJECT-TYPE
			SYNTAX	INTEGER
			MAX-ACCESS	read-only
			STATUS	current
			::= { hmWanMbus52 57 }

hmWanMbus52VIF1A		OBJECT-TYPE
			SYNTAX	INTEGER
			MAX-ACCESS	read-only
			STATUS	current
			::= { hmWanMbus52 58 }

hmWanMbus52Value1A		OBJECT-TYPE
			SYNTAX	INTEGER
			MAX-ACCESS	read-only
			STATUS	current
			::= { hmWanMbus52 59 }

hmWanMbus52VIF1B		OBJECT-TYPE
			SYNTAX	INTEGER
			MAX-ACCESS	read-only
			STATUS	current
			::= { hmWanMbus52 60 }

hmWanMbus52Value1B		OBJECT-TYPE
			SYNTAX	INTEGER
			MAX-ACCESS	read-only
			STATUS	current
			::= { hmWanMbus52 61 }

hmWanMbus52VIF1C		OBJECT-TYPE
			SYNTAX	INTEGER
			MAX-ACCESS	read-only
			STATUS	current
			::= { hmWanMbus52 62 }

hmWanMbus52Value1C		OBJECT-TYPE
			SYNTAX	INTEGER
			MAX-ACCESS	read-only
			STATUS	current
			::= { hmWanMbus52 63 }

hmWanMbus52VIF1D		OBJECT-TYPE
			SYNTAX	INTEGER
			MAX-ACCESS	read-only
			STATUS	current
			::= { hmWanMbus52 64 }

hmWanMbus52Value1D		OBJECT-TYPE
			SYNTAX	INTEGER
			MAX-ACCESS	read-only
			STATUS	current
			::= { hmWanMbus52 65 }

hmWanMbus52VIF1E		OBJECT-TYPE
			SYNTAX	INTEGER
			MAX-ACCESS	read-only
			STATUS	current
			::= { hmWanMbus52 66 }

hmWanMbus52Value1E		OBJECT-TYPE
			SYNTAX	INTEGER
			MAX-ACCESS	read-only
			STATUS	current
			::= { hmWanMbus52 67 }

hmWanMbus52VIF1F		OBJECT-TYPE
			SYNTAX	INTEGER
			MAX-ACCESS	read-only
			STATUS	current
			::= { hmWanMbus52 68 }

hmWanMbus52Value1F		OBJECT-TYPE
			SYNTAX	INTEGER
			MAX-ACCESS	read-only
			STATUS	current
			::= { hmWanMbus52 69 }

hmWanMbus52VIF20		OBJECT-TYPE
			SYNTAX	INTEGER
			MAX-ACCESS	read-only
			STATUS	current
			::= { hmWanMbus52 70 }

hmWanMbus52Value20		OBJECT-TYPE
			SYNTAX	INTEGER
			MAX-ACCESS	read-only
			STATUS	current
			::= { hmWanMbus52 71 }

hmWanMbus52VIF21		OBJECT-TYPE
			SYNTAX	INTEGER
			MAX-ACCESS	read-only
			STATUS	current
			::= { hmWanMbus52 72 }

hmWanMbus52Value21		OBJECT-TYPE
			SYNTAX	INTEGER
			MAX-ACCESS	read-only
			STATUS	current
			::= { hmWanMbus52 73 }

hmWanMbus52VIF22		OBJECT-TYPE
			SYNTAX	INTEGER
			MAX-ACCESS	read-only
			STATUS	current
			::= { hmWanMbus52 74 }

hmWanMbus52Value22		OBJECT-TYPE
			SYNTAX	INTEGER
			MAX-ACCESS	read-only
			STATUS	current
			::= { hmWanMbus52 75 }

hmWanMbus52VIF23		OBJECT-TYPE
			SYNTAX	INTEGER
			MAX-ACCESS	read-only
			STATUS	current
			::= { hmWanMbus52 76 }

hmWanMbus52Value23		OBJECT-TYPE
			SYNTAX	INTEGER
			MAX-ACCESS	read-only
			STATUS	current
			::= { hmWanMbus52 77 }

hmWanMbus52VIF24		OBJECT-TYPE
			SYNTAX	INTEGER
			MAX-ACCESS	read-only
			STATUS	current
			::= { hmWanMbus52 78 }

hmWanMbus52Value24		OBJECT-TYPE
			SYNTAX	INTEGER
			MAX-ACCESS	read-only
			STATUS	current
			::= { hmWanMbus52 79 }

hmWanMbus52VIF25		OBJECT-TYPE
			SYNTAX	INTEGER
			MAX-ACCESS	read-only
			STATUS	current
			::= { hmWanMbus52 80 }

hmWanMbus52Value25		OBJECT-TYPE
			SYNTAX	INTEGER
			MAX-ACCESS	read-only
			STATUS	current
			::= { hmWanMbus52 81 }

hmWanMbus52VIF26		OBJECT-TYPE
			SYNTAX	INTEGER
			MAX-ACCESS	read-only
			STATUS	current
			::= { hmWanMbus52 82 }

hmWanMbus52Value26		OBJECT-TYPE
			SYNTAX	INTEGER
			MAX-ACCESS	read-only
			STATUS	current
			::= { hmWanMbus52 83 }

hmWanMbus52VIF27		OBJECT-TYPE
			SYNTAX	INTEGER
			MAX-ACCESS	read-only
			STATUS	current
			::= { hmWanMbus52 84 }

hmWanMbus52Value27		OBJECT-TYPE
			SYNTAX	INTEGER
			MAX-ACCESS	read-only
			STATUS	current
			::= { hmWanMbus52 85 }

hmWanMbus52VIF28		OBJECT-TYPE
			SYNTAX	INTEGER
			MAX-ACCESS	read-only
			STATUS	current
			::= { hmWanMbus52 86 }

hmWanMbus52Value28		OBJECT-TYPE
			SYNTAX	INTEGER
			MAX-ACCESS	read-only
			STATUS	current
			::= { hmWanMbus52 87 }

hmWanMbus52VIF29		OBJECT-TYPE
			SYNTAX	INTEGER
			MAX-ACCESS	read-only
			STATUS	current
			::= { hmWanMbus52 88 }

hmWanMbus52Value29		OBJECT-TYPE
			SYNTAX	INTEGER
			MAX-ACCESS	read-only
			STATUS	current
			::= { hmWanMbus52 89 }

hmWanMbus52VIF2A		OBJECT-TYPE
			SYNTAX	INTEGER
			MAX-ACCESS	read-only
			STATUS	current
			::= { hmWanMbus52 90 }

hmWanMbus52Value2A		OBJECT-TYPE
			SYNTAX	INTEGER
			MAX-ACCESS	read-only
			STATUS	current
			::= { hmWanMbus52 91 }

hmWanMbus52VIF2B		OBJECT-TYPE
			SYNTAX	INTEGER
			MAX-ACCESS	read-only
			STATUS	current
			::= { hmWanMbus52 92 }

hmWanMbus52Value2B		OBJECT-TYPE
			SYNTAX	INTEGER
			MAX-ACCESS	read-only
			STATUS	current
			::= { hmWanMbus52 93 }

hmWanMbus52VIF2C		OBJECT-TYPE
			SYNTAX	INTEGER
			MAX-ACCESS	read-only
			STATUS	current
			::= { hmWanMbus52 94 }

hmWanMbus52Value2C		OBJECT-TYPE
			SYNTAX	INTEGER
			MAX-ACCESS	read-only
			STATUS	current
			::= { hmWanMbus52 95 }

hmWanMbus52VIF2D		OBJECT-TYPE
			SYNTAX	INTEGER
			MAX-ACCESS	read-only
			STATUS	current
			::= { hmWanMbus52 96 }

hmWanMbus52Value2D		OBJECT-TYPE
			SYNTAX	INTEGER
			MAX-ACCESS	read-only
			STATUS	current
			::= { hmWanMbus52 97 }

hmWanMbus52VIF2E		OBJECT-TYPE
			SYNTAX	INTEGER
			MAX-ACCESS	read-only
			STATUS	current
			::= { hmWanMbus52 98 }

hmWanMbus52Value2E		OBJECT-TYPE
			SYNTAX	INTEGER
			MAX-ACCESS	read-only
			STATUS	current
			::= { hmWanMbus52 99 }

hmWanMbus52VIF2F		OBJECT-TYPE
			SYNTAX	INTEGER
			MAX-ACCESS	read-only
			STATUS	current
			::= { hmWanMbus52 100 }

hmWanMbus52Value2F		OBJECT-TYPE
			SYNTAX	INTEGER
			MAX-ACCESS	read-only
			STATUS	current
			::= { hmWanMbus52 101 }

hmWanMbus53			OBJECT IDENTIFIER ::= { hmWanMbus 83 }

hmWanMbus53IdNumber		OBJECT-TYPE
			SYNTAX	Gauge32
			MAX-ACCESS	read-only
			STATUS	current
			::= { hmWanMbus53 1 }

hmWanMbus53Manufacturer	OBJECT-TYPE
			SYNTAX	Gauge32
			MAX-ACCESS	read-only
			STATUS	current
			::= { hmWanMbus53 2 }

hmWanMbus53Version		OBJECT-TYPE
			SYNTAX	Gauge32
			MAX-ACCESS	read-only
			STATUS	current
			::= { hmWanMbus53 3 }

hmWanMbus53Medium		OBJECT-TYPE
			SYNTAX	Gauge32
			MAX-ACCESS	read-only
			STATUS	current
			::= { hmWanMbus53 4 }

hmWanMbus53Status		OBJECT-TYPE
			SYNTAX	Gauge32
			MAX-ACCESS	read-only
			STATUS	current
			::= { hmWanMbus53 5 }

hmWanMbus53VIF00		OBJECT-TYPE
			SYNTAX	INTEGER
			MAX-ACCESS	read-only
			STATUS	current
			::= { hmWanMbus53 6 }

hmWanMbus53Value00		OBJECT-TYPE
			SYNTAX	INTEGER
			MAX-ACCESS	read-only
			STATUS	current
			::= { hmWanMbus53 7 }

hmWanMbus53VIF01		OBJECT-TYPE
			SYNTAX	INTEGER
			MAX-ACCESS	read-only
			STATUS	current
			::= { hmWanMbus53 8 }

hmWanMbus53Value01		OBJECT-TYPE
			SYNTAX	INTEGER
			MAX-ACCESS	read-only
			STATUS	current
			::= { hmWanMbus53 9 }

hmWanMbus53VIF02		OBJECT-TYPE
			SYNTAX	INTEGER
			MAX-ACCESS	read-only
			STATUS	current
			::= { hmWanMbus53 10 }

hmWanMbus53Value02		OBJECT-TYPE
			SYNTAX	INTEGER
			MAX-ACCESS	read-only
			STATUS	current
			::= { hmWanMbus53 11 }

hmWanMbus53VIF03		OBJECT-TYPE
			SYNTAX	INTEGER
			MAX-ACCESS	read-only
			STATUS	current
			::= { hmWanMbus53 12 }

hmWanMbus53Value03		OBJECT-TYPE
			SYNTAX	INTEGER
			MAX-ACCESS	read-only
			STATUS	current
			::= { hmWanMbus53 13 }

hmWanMbus53VIF04		OBJECT-TYPE
			SYNTAX	INTEGER
			MAX-ACCESS	read-only
			STATUS	current
			::= { hmWanMbus53 14 }

hmWanMbus53Value04		OBJECT-TYPE
			SYNTAX	INTEGER
			MAX-ACCESS	read-only
			STATUS	current
			::= { hmWanMbus53 15 }

hmWanMbus53VIF05		OBJECT-TYPE
			SYNTAX	INTEGER
			MAX-ACCESS	read-only
			STATUS	current
			::= { hmWanMbus53 16 }

hmWanMbus53Value05		OBJECT-TYPE
			SYNTAX	INTEGER
			MAX-ACCESS	read-only
			STATUS	current
			::= { hmWanMbus53 17 }

hmWanMbus53VIF06		OBJECT-TYPE
			SYNTAX	INTEGER
			MAX-ACCESS	read-only
			STATUS	current
			::= { hmWanMbus53 18 }

hmWanMbus53Value06		OBJECT-TYPE
			SYNTAX	INTEGER
			MAX-ACCESS	read-only
			STATUS	current
			::= { hmWanMbus53 19 }

hmWanMbus53VIF07		OBJECT-TYPE
			SYNTAX	INTEGER
			MAX-ACCESS	read-only
			STATUS	current
			::= { hmWanMbus53 20 }

hmWanMbus53Value07		OBJECT-TYPE
			SYNTAX	INTEGER
			MAX-ACCESS	read-only
			STATUS	current
			::= { hmWanMbus53 21 }

hmWanMbus53VIF08		OBJECT-TYPE
			SYNTAX	INTEGER
			MAX-ACCESS	read-only
			STATUS	current
			::= { hmWanMbus53 22 }

hmWanMbus53Value08		OBJECT-TYPE
			SYNTAX	INTEGER
			MAX-ACCESS	read-only
			STATUS	current
			::= { hmWanMbus53 23 }

hmWanMbus53VIF09		OBJECT-TYPE
			SYNTAX	INTEGER
			MAX-ACCESS	read-only
			STATUS	current
			::= { hmWanMbus53 24 }

hmWanMbus53Value09		OBJECT-TYPE
			SYNTAX	INTEGER
			MAX-ACCESS	read-only
			STATUS	current
			::= { hmWanMbus53 25 }

hmWanMbus53VIF0A		OBJECT-TYPE
			SYNTAX	INTEGER
			MAX-ACCESS	read-only
			STATUS	current
			::= { hmWanMbus53 26 }

hmWanMbus53Value0A		OBJECT-TYPE
			SYNTAX	INTEGER
			MAX-ACCESS	read-only
			STATUS	current
			::= { hmWanMbus53 27 }

hmWanMbus53VIF0B		OBJECT-TYPE
			SYNTAX	INTEGER
			MAX-ACCESS	read-only
			STATUS	current
			::= { hmWanMbus53 28 }

hmWanMbus53Value0B		OBJECT-TYPE
			SYNTAX	INTEGER
			MAX-ACCESS	read-only
			STATUS	current
			::= { hmWanMbus53 29 }

hmWanMbus53VIF0C		OBJECT-TYPE
			SYNTAX	INTEGER
			MAX-ACCESS	read-only
			STATUS	current
			::= { hmWanMbus53 30 }

hmWanMbus53Value0C		OBJECT-TYPE
			SYNTAX	INTEGER
			MAX-ACCESS	read-only
			STATUS	current
			::= { hmWanMbus53 31 }

hmWanMbus53VIF0D		OBJECT-TYPE
			SYNTAX	INTEGER
			MAX-ACCESS	read-only
			STATUS	current
			::= { hmWanMbus53 32 }

hmWanMbus53Value0D		OBJECT-TYPE
			SYNTAX	INTEGER
			MAX-ACCESS	read-only
			STATUS	current
			::= { hmWanMbus53 33 }

hmWanMbus53VIF0E		OBJECT-TYPE
			SYNTAX	INTEGER
			MAX-ACCESS	read-only
			STATUS	current
			::= { hmWanMbus53 34 }

hmWanMbus53Value0E		OBJECT-TYPE
			SYNTAX	INTEGER
			MAX-ACCESS	read-only
			STATUS	current
			::= { hmWanMbus53 35 }

hmWanMbus53VIF0F		OBJECT-TYPE
			SYNTAX	INTEGER
			MAX-ACCESS	read-only
			STATUS	current
			::= { hmWanMbus53 36 }

hmWanMbus53Value0F		OBJECT-TYPE
			SYNTAX	INTEGER
			MAX-ACCESS	read-only
			STATUS	current
			::= { hmWanMbus53 37 }

hmWanMbus53VIF10		OBJECT-TYPE
			SYNTAX	INTEGER
			MAX-ACCESS	read-only
			STATUS	current
			::= { hmWanMbus53 38 }

hmWanMbus53Value10		OBJECT-TYPE
			SYNTAX	INTEGER
			MAX-ACCESS	read-only
			STATUS	current
			::= { hmWanMbus53 39 }

hmWanMbus53VIF11		OBJECT-TYPE
			SYNTAX	INTEGER
			MAX-ACCESS	read-only
			STATUS	current
			::= { hmWanMbus53 40 }

hmWanMbus53Value11		OBJECT-TYPE
			SYNTAX	INTEGER
			MAX-ACCESS	read-only
			STATUS	current
			::= { hmWanMbus53 41 }

hmWanMbus53VIF12		OBJECT-TYPE
			SYNTAX	INTEGER
			MAX-ACCESS	read-only
			STATUS	current
			::= { hmWanMbus53 42 }

hmWanMbus53Value12		OBJECT-TYPE
			SYNTAX	INTEGER
			MAX-ACCESS	read-only
			STATUS	current
			::= { hmWanMbus53 43 }

hmWanMbus53VIF13		OBJECT-TYPE
			SYNTAX	INTEGER
			MAX-ACCESS	read-only
			STATUS	current
			::= { hmWanMbus53 44 }

hmWanMbus53Value13		OBJECT-TYPE
			SYNTAX	INTEGER
			MAX-ACCESS	read-only
			STATUS	current
			::= { hmWanMbus53 45 }

hmWanMbus53VIF14		OBJECT-TYPE
			SYNTAX	INTEGER
			MAX-ACCESS	read-only
			STATUS	current
			::= { hmWanMbus53 46 }

hmWanMbus53Value14		OBJECT-TYPE
			SYNTAX	INTEGER
			MAX-ACCESS	read-only
			STATUS	current
			::= { hmWanMbus53 47 }

hmWanMbus53VIF15		OBJECT-TYPE
			SYNTAX	INTEGER
			MAX-ACCESS	read-only
			STATUS	current
			::= { hmWanMbus53 48 }

hmWanMbus53Value15		OBJECT-TYPE
			SYNTAX	INTEGER
			MAX-ACCESS	read-only
			STATUS	current
			::= { hmWanMbus53 49 }

hmWanMbus53VIF16		OBJECT-TYPE
			SYNTAX	INTEGER
			MAX-ACCESS	read-only
			STATUS	current
			::= { hmWanMbus53 50 }

hmWanMbus53Value16		OBJECT-TYPE
			SYNTAX	INTEGER
			MAX-ACCESS	read-only
			STATUS	current
			::= { hmWanMbus53 51 }

hmWanMbus53VIF17		OBJECT-TYPE
			SYNTAX	INTEGER
			MAX-ACCESS	read-only
			STATUS	current
			::= { hmWanMbus53 52 }

hmWanMbus53Value17		OBJECT-TYPE
			SYNTAX	INTEGER
			MAX-ACCESS	read-only
			STATUS	current
			::= { hmWanMbus53 53 }

hmWanMbus53VIF18		OBJECT-TYPE
			SYNTAX	INTEGER
			MAX-ACCESS	read-only
			STATUS	current
			::= { hmWanMbus53 54 }

hmWanMbus53Value18		OBJECT-TYPE
			SYNTAX	INTEGER
			MAX-ACCESS	read-only
			STATUS	current
			::= { hmWanMbus53 55 }

hmWanMbus53VIF19		OBJECT-TYPE
			SYNTAX	INTEGER
			MAX-ACCESS	read-only
			STATUS	current
			::= { hmWanMbus53 56 }

hmWanMbus53Value19		OBJECT-TYPE
			SYNTAX	INTEGER
			MAX-ACCESS	read-only
			STATUS	current
			::= { hmWanMbus53 57 }

hmWanMbus53VIF1A		OBJECT-TYPE
			SYNTAX	INTEGER
			MAX-ACCESS	read-only
			STATUS	current
			::= { hmWanMbus53 58 }

hmWanMbus53Value1A		OBJECT-TYPE
			SYNTAX	INTEGER
			MAX-ACCESS	read-only
			STATUS	current
			::= { hmWanMbus53 59 }

hmWanMbus53VIF1B		OBJECT-TYPE
			SYNTAX	INTEGER
			MAX-ACCESS	read-only
			STATUS	current
			::= { hmWanMbus53 60 }

hmWanMbus53Value1B		OBJECT-TYPE
			SYNTAX	INTEGER
			MAX-ACCESS	read-only
			STATUS	current
			::= { hmWanMbus53 61 }

hmWanMbus53VIF1C		OBJECT-TYPE
			SYNTAX	INTEGER
			MAX-ACCESS	read-only
			STATUS	current
			::= { hmWanMbus53 62 }

hmWanMbus53Value1C		OBJECT-TYPE
			SYNTAX	INTEGER
			MAX-ACCESS	read-only
			STATUS	current
			::= { hmWanMbus53 63 }

hmWanMbus53VIF1D		OBJECT-TYPE
			SYNTAX	INTEGER
			MAX-ACCESS	read-only
			STATUS	current
			::= { hmWanMbus53 64 }

hmWanMbus53Value1D		OBJECT-TYPE
			SYNTAX	INTEGER
			MAX-ACCESS	read-only
			STATUS	current
			::= { hmWanMbus53 65 }

hmWanMbus53VIF1E		OBJECT-TYPE
			SYNTAX	INTEGER
			MAX-ACCESS	read-only
			STATUS	current
			::= { hmWanMbus53 66 }

hmWanMbus53Value1E		OBJECT-TYPE
			SYNTAX	INTEGER
			MAX-ACCESS	read-only
			STATUS	current
			::= { hmWanMbus53 67 }

hmWanMbus53VIF1F		OBJECT-TYPE
			SYNTAX	INTEGER
			MAX-ACCESS	read-only
			STATUS	current
			::= { hmWanMbus53 68 }

hmWanMbus53Value1F		OBJECT-TYPE
			SYNTAX	INTEGER
			MAX-ACCESS	read-only
			STATUS	current
			::= { hmWanMbus53 69 }

hmWanMbus53VIF20		OBJECT-TYPE
			SYNTAX	INTEGER
			MAX-ACCESS	read-only
			STATUS	current
			::= { hmWanMbus53 70 }

hmWanMbus53Value20		OBJECT-TYPE
			SYNTAX	INTEGER
			MAX-ACCESS	read-only
			STATUS	current
			::= { hmWanMbus53 71 }

hmWanMbus53VIF21		OBJECT-TYPE
			SYNTAX	INTEGER
			MAX-ACCESS	read-only
			STATUS	current
			::= { hmWanMbus53 72 }

hmWanMbus53Value21		OBJECT-TYPE
			SYNTAX	INTEGER
			MAX-ACCESS	read-only
			STATUS	current
			::= { hmWanMbus53 73 }

hmWanMbus53VIF22		OBJECT-TYPE
			SYNTAX	INTEGER
			MAX-ACCESS	read-only
			STATUS	current
			::= { hmWanMbus53 74 }

hmWanMbus53Value22		OBJECT-TYPE
			SYNTAX	INTEGER
			MAX-ACCESS	read-only
			STATUS	current
			::= { hmWanMbus53 75 }

hmWanMbus53VIF23		OBJECT-TYPE
			SYNTAX	INTEGER
			MAX-ACCESS	read-only
			STATUS	current
			::= { hmWanMbus53 76 }

hmWanMbus53Value23		OBJECT-TYPE
			SYNTAX	INTEGER
			MAX-ACCESS	read-only
			STATUS	current
			::= { hmWanMbus53 77 }

hmWanMbus53VIF24		OBJECT-TYPE
			SYNTAX	INTEGER
			MAX-ACCESS	read-only
			STATUS	current
			::= { hmWanMbus53 78 }

hmWanMbus53Value24		OBJECT-TYPE
			SYNTAX	INTEGER
			MAX-ACCESS	read-only
			STATUS	current
			::= { hmWanMbus53 79 }

hmWanMbus53VIF25		OBJECT-TYPE
			SYNTAX	INTEGER
			MAX-ACCESS	read-only
			STATUS	current
			::= { hmWanMbus53 80 }

hmWanMbus53Value25		OBJECT-TYPE
			SYNTAX	INTEGER
			MAX-ACCESS	read-only
			STATUS	current
			::= { hmWanMbus53 81 }

hmWanMbus53VIF26		OBJECT-TYPE
			SYNTAX	INTEGER
			MAX-ACCESS	read-only
			STATUS	current
			::= { hmWanMbus53 82 }

hmWanMbus53Value26		OBJECT-TYPE
			SYNTAX	INTEGER
			MAX-ACCESS	read-only
			STATUS	current
			::= { hmWanMbus53 83 }

hmWanMbus53VIF27		OBJECT-TYPE
			SYNTAX	INTEGER
			MAX-ACCESS	read-only
			STATUS	current
			::= { hmWanMbus53 84 }

hmWanMbus53Value27		OBJECT-TYPE
			SYNTAX	INTEGER
			MAX-ACCESS	read-only
			STATUS	current
			::= { hmWanMbus53 85 }

hmWanMbus53VIF28		OBJECT-TYPE
			SYNTAX	INTEGER
			MAX-ACCESS	read-only
			STATUS	current
			::= { hmWanMbus53 86 }

hmWanMbus53Value28		OBJECT-TYPE
			SYNTAX	INTEGER
			MAX-ACCESS	read-only
			STATUS	current
			::= { hmWanMbus53 87 }

hmWanMbus53VIF29		OBJECT-TYPE
			SYNTAX	INTEGER
			MAX-ACCESS	read-only
			STATUS	current
			::= { hmWanMbus53 88 }

hmWanMbus53Value29		OBJECT-TYPE
			SYNTAX	INTEGER
			MAX-ACCESS	read-only
			STATUS	current
			::= { hmWanMbus53 89 }

hmWanMbus53VIF2A		OBJECT-TYPE
			SYNTAX	INTEGER
			MAX-ACCESS	read-only
			STATUS	current
			::= { hmWanMbus53 90 }

hmWanMbus53Value2A		OBJECT-TYPE
			SYNTAX	INTEGER
			MAX-ACCESS	read-only
			STATUS	current
			::= { hmWanMbus53 91 }

hmWanMbus53VIF2B		OBJECT-TYPE
			SYNTAX	INTEGER
			MAX-ACCESS	read-only
			STATUS	current
			::= { hmWanMbus53 92 }

hmWanMbus53Value2B		OBJECT-TYPE
			SYNTAX	INTEGER
			MAX-ACCESS	read-only
			STATUS	current
			::= { hmWanMbus53 93 }

hmWanMbus53VIF2C		OBJECT-TYPE
			SYNTAX	INTEGER
			MAX-ACCESS	read-only
			STATUS	current
			::= { hmWanMbus53 94 }

hmWanMbus53Value2C		OBJECT-TYPE
			SYNTAX	INTEGER
			MAX-ACCESS	read-only
			STATUS	current
			::= { hmWanMbus53 95 }

hmWanMbus53VIF2D		OBJECT-TYPE
			SYNTAX	INTEGER
			MAX-ACCESS	read-only
			STATUS	current
			::= { hmWanMbus53 96 }

hmWanMbus53Value2D		OBJECT-TYPE
			SYNTAX	INTEGER
			MAX-ACCESS	read-only
			STATUS	current
			::= { hmWanMbus53 97 }

hmWanMbus53VIF2E		OBJECT-TYPE
			SYNTAX	INTEGER
			MAX-ACCESS	read-only
			STATUS	current
			::= { hmWanMbus53 98 }

hmWanMbus53Value2E		OBJECT-TYPE
			SYNTAX	INTEGER
			MAX-ACCESS	read-only
			STATUS	current
			::= { hmWanMbus53 99 }

hmWanMbus53VIF2F		OBJECT-TYPE
			SYNTAX	INTEGER
			MAX-ACCESS	read-only
			STATUS	current
			::= { hmWanMbus53 100 }

hmWanMbus53Value2F		OBJECT-TYPE
			SYNTAX	INTEGER
			MAX-ACCESS	read-only
			STATUS	current
			::= { hmWanMbus53 101 }

hmWanMbus54			OBJECT IDENTIFIER ::= { hmWanMbus 84 }

hmWanMbus54IdNumber		OBJECT-TYPE
			SYNTAX	Gauge32
			MAX-ACCESS	read-only
			STATUS	current
			::= { hmWanMbus54 1 }

hmWanMbus54Manufacturer	OBJECT-TYPE
			SYNTAX	Gauge32
			MAX-ACCESS	read-only
			STATUS	current
			::= { hmWanMbus54 2 }

hmWanMbus54Version		OBJECT-TYPE
			SYNTAX	Gauge32
			MAX-ACCESS	read-only
			STATUS	current
			::= { hmWanMbus54 3 }

hmWanMbus54Medium		OBJECT-TYPE
			SYNTAX	Gauge32
			MAX-ACCESS	read-only
			STATUS	current
			::= { hmWanMbus54 4 }

hmWanMbus54Status		OBJECT-TYPE
			SYNTAX	Gauge32
			MAX-ACCESS	read-only
			STATUS	current
			::= { hmWanMbus54 5 }

hmWanMbus54VIF00		OBJECT-TYPE
			SYNTAX	INTEGER
			MAX-ACCESS	read-only
			STATUS	current
			::= { hmWanMbus54 6 }

hmWanMbus54Value00		OBJECT-TYPE
			SYNTAX	INTEGER
			MAX-ACCESS	read-only
			STATUS	current
			::= { hmWanMbus54 7 }

hmWanMbus54VIF01		OBJECT-TYPE
			SYNTAX	INTEGER
			MAX-ACCESS	read-only
			STATUS	current
			::= { hmWanMbus54 8 }

hmWanMbus54Value01		OBJECT-TYPE
			SYNTAX	INTEGER
			MAX-ACCESS	read-only
			STATUS	current
			::= { hmWanMbus54 9 }

hmWanMbus54VIF02		OBJECT-TYPE
			SYNTAX	INTEGER
			MAX-ACCESS	read-only
			STATUS	current
			::= { hmWanMbus54 10 }

hmWanMbus54Value02		OBJECT-TYPE
			SYNTAX	INTEGER
			MAX-ACCESS	read-only
			STATUS	current
			::= { hmWanMbus54 11 }

hmWanMbus54VIF03		OBJECT-TYPE
			SYNTAX	INTEGER
			MAX-ACCESS	read-only
			STATUS	current
			::= { hmWanMbus54 12 }

hmWanMbus54Value03		OBJECT-TYPE
			SYNTAX	INTEGER
			MAX-ACCESS	read-only
			STATUS	current
			::= { hmWanMbus54 13 }

hmWanMbus54VIF04		OBJECT-TYPE
			SYNTAX	INTEGER
			MAX-ACCESS	read-only
			STATUS	current
			::= { hmWanMbus54 14 }

hmWanMbus54Value04		OBJECT-TYPE
			SYNTAX	INTEGER
			MAX-ACCESS	read-only
			STATUS	current
			::= { hmWanMbus54 15 }

hmWanMbus54VIF05		OBJECT-TYPE
			SYNTAX	INTEGER
			MAX-ACCESS	read-only
			STATUS	current
			::= { hmWanMbus54 16 }

hmWanMbus54Value05		OBJECT-TYPE
			SYNTAX	INTEGER
			MAX-ACCESS	read-only
			STATUS	current
			::= { hmWanMbus54 17 }

hmWanMbus54VIF06		OBJECT-TYPE
			SYNTAX	INTEGER
			MAX-ACCESS	read-only
			STATUS	current
			::= { hmWanMbus54 18 }

hmWanMbus54Value06		OBJECT-TYPE
			SYNTAX	INTEGER
			MAX-ACCESS	read-only
			STATUS	current
			::= { hmWanMbus54 19 }

hmWanMbus54VIF07		OBJECT-TYPE
			SYNTAX	INTEGER
			MAX-ACCESS	read-only
			STATUS	current
			::= { hmWanMbus54 20 }

hmWanMbus54Value07		OBJECT-TYPE
			SYNTAX	INTEGER
			MAX-ACCESS	read-only
			STATUS	current
			::= { hmWanMbus54 21 }

hmWanMbus54VIF08		OBJECT-TYPE
			SYNTAX	INTEGER
			MAX-ACCESS	read-only
			STATUS	current
			::= { hmWanMbus54 22 }

hmWanMbus54Value08		OBJECT-TYPE
			SYNTAX	INTEGER
			MAX-ACCESS	read-only
			STATUS	current
			::= { hmWanMbus54 23 }

hmWanMbus54VIF09		OBJECT-TYPE
			SYNTAX	INTEGER
			MAX-ACCESS	read-only
			STATUS	current
			::= { hmWanMbus54 24 }

hmWanMbus54Value09		OBJECT-TYPE
			SYNTAX	INTEGER
			MAX-ACCESS	read-only
			STATUS	current
			::= { hmWanMbus54 25 }

hmWanMbus54VIF0A		OBJECT-TYPE
			SYNTAX	INTEGER
			MAX-ACCESS	read-only
			STATUS	current
			::= { hmWanMbus54 26 }

hmWanMbus54Value0A		OBJECT-TYPE
			SYNTAX	INTEGER
			MAX-ACCESS	read-only
			STATUS	current
			::= { hmWanMbus54 27 }

hmWanMbus54VIF0B		OBJECT-TYPE
			SYNTAX	INTEGER
			MAX-ACCESS	read-only
			STATUS	current
			::= { hmWanMbus54 28 }

hmWanMbus54Value0B		OBJECT-TYPE
			SYNTAX	INTEGER
			MAX-ACCESS	read-only
			STATUS	current
			::= { hmWanMbus54 29 }

hmWanMbus54VIF0C		OBJECT-TYPE
			SYNTAX	INTEGER
			MAX-ACCESS	read-only
			STATUS	current
			::= { hmWanMbus54 30 }

hmWanMbus54Value0C		OBJECT-TYPE
			SYNTAX	INTEGER
			MAX-ACCESS	read-only
			STATUS	current
			::= { hmWanMbus54 31 }

hmWanMbus54VIF0D		OBJECT-TYPE
			SYNTAX	INTEGER
			MAX-ACCESS	read-only
			STATUS	current
			::= { hmWanMbus54 32 }

hmWanMbus54Value0D		OBJECT-TYPE
			SYNTAX	INTEGER
			MAX-ACCESS	read-only
			STATUS	current
			::= { hmWanMbus54 33 }

hmWanMbus54VIF0E		OBJECT-TYPE
			SYNTAX	INTEGER
			MAX-ACCESS	read-only
			STATUS	current
			::= { hmWanMbus54 34 }

hmWanMbus54Value0E		OBJECT-TYPE
			SYNTAX	INTEGER
			MAX-ACCESS	read-only
			STATUS	current
			::= { hmWanMbus54 35 }

hmWanMbus54VIF0F		OBJECT-TYPE
			SYNTAX	INTEGER
			MAX-ACCESS	read-only
			STATUS	current
			::= { hmWanMbus54 36 }

hmWanMbus54Value0F		OBJECT-TYPE
			SYNTAX	INTEGER
			MAX-ACCESS	read-only
			STATUS	current
			::= { hmWanMbus54 37 }

hmWanMbus54VIF10		OBJECT-TYPE
			SYNTAX	INTEGER
			MAX-ACCESS	read-only
			STATUS	current
			::= { hmWanMbus54 38 }

hmWanMbus54Value10		OBJECT-TYPE
			SYNTAX	INTEGER
			MAX-ACCESS	read-only
			STATUS	current
			::= { hmWanMbus54 39 }

hmWanMbus54VIF11		OBJECT-TYPE
			SYNTAX	INTEGER
			MAX-ACCESS	read-only
			STATUS	current
			::= { hmWanMbus54 40 }

hmWanMbus54Value11		OBJECT-TYPE
			SYNTAX	INTEGER
			MAX-ACCESS	read-only
			STATUS	current
			::= { hmWanMbus54 41 }

hmWanMbus54VIF12		OBJECT-TYPE
			SYNTAX	INTEGER
			MAX-ACCESS	read-only
			STATUS	current
			::= { hmWanMbus54 42 }

hmWanMbus54Value12		OBJECT-TYPE
			SYNTAX	INTEGER
			MAX-ACCESS	read-only
			STATUS	current
			::= { hmWanMbus54 43 }

hmWanMbus54VIF13		OBJECT-TYPE
			SYNTAX	INTEGER
			MAX-ACCESS	read-only
			STATUS	current
			::= { hmWanMbus54 44 }

hmWanMbus54Value13		OBJECT-TYPE
			SYNTAX	INTEGER
			MAX-ACCESS	read-only
			STATUS	current
			::= { hmWanMbus54 45 }

hmWanMbus54VIF14		OBJECT-TYPE
			SYNTAX	INTEGER
			MAX-ACCESS	read-only
			STATUS	current
			::= { hmWanMbus54 46 }

hmWanMbus54Value14		OBJECT-TYPE
			SYNTAX	INTEGER
			MAX-ACCESS	read-only
			STATUS	current
			::= { hmWanMbus54 47 }

hmWanMbus54VIF15		OBJECT-TYPE
			SYNTAX	INTEGER
			MAX-ACCESS	read-only
			STATUS	current
			::= { hmWanMbus54 48 }

hmWanMbus54Value15		OBJECT-TYPE
			SYNTAX	INTEGER
			MAX-ACCESS	read-only
			STATUS	current
			::= { hmWanMbus54 49 }

hmWanMbus54VIF16		OBJECT-TYPE
			SYNTAX	INTEGER
			MAX-ACCESS	read-only
			STATUS	current
			::= { hmWanMbus54 50 }

hmWanMbus54Value16		OBJECT-TYPE
			SYNTAX	INTEGER
			MAX-ACCESS	read-only
			STATUS	current
			::= { hmWanMbus54 51 }

hmWanMbus54VIF17		OBJECT-TYPE
			SYNTAX	INTEGER
			MAX-ACCESS	read-only
			STATUS	current
			::= { hmWanMbus54 52 }

hmWanMbus54Value17		OBJECT-TYPE
			SYNTAX	INTEGER
			MAX-ACCESS	read-only
			STATUS	current
			::= { hmWanMbus54 53 }

hmWanMbus54VIF18		OBJECT-TYPE
			SYNTAX	INTEGER
			MAX-ACCESS	read-only
			STATUS	current
			::= { hmWanMbus54 54 }

hmWanMbus54Value18		OBJECT-TYPE
			SYNTAX	INTEGER
			MAX-ACCESS	read-only
			STATUS	current
			::= { hmWanMbus54 55 }

hmWanMbus54VIF19		OBJECT-TYPE
			SYNTAX	INTEGER
			MAX-ACCESS	read-only
			STATUS	current
			::= { hmWanMbus54 56 }

hmWanMbus54Value19		OBJECT-TYPE
			SYNTAX	INTEGER
			MAX-ACCESS	read-only
			STATUS	current
			::= { hmWanMbus54 57 }

hmWanMbus54VIF1A		OBJECT-TYPE
			SYNTAX	INTEGER
			MAX-ACCESS	read-only
			STATUS	current
			::= { hmWanMbus54 58 }

hmWanMbus54Value1A		OBJECT-TYPE
			SYNTAX	INTEGER
			MAX-ACCESS	read-only
			STATUS	current
			::= { hmWanMbus54 59 }

hmWanMbus54VIF1B		OBJECT-TYPE
			SYNTAX	INTEGER
			MAX-ACCESS	read-only
			STATUS	current
			::= { hmWanMbus54 60 }

hmWanMbus54Value1B		OBJECT-TYPE
			SYNTAX	INTEGER
			MAX-ACCESS	read-only
			STATUS	current
			::= { hmWanMbus54 61 }

hmWanMbus54VIF1C		OBJECT-TYPE
			SYNTAX	INTEGER
			MAX-ACCESS	read-only
			STATUS	current
			::= { hmWanMbus54 62 }

hmWanMbus54Value1C		OBJECT-TYPE
			SYNTAX	INTEGER
			MAX-ACCESS	read-only
			STATUS	current
			::= { hmWanMbus54 63 }

hmWanMbus54VIF1D		OBJECT-TYPE
			SYNTAX	INTEGER
			MAX-ACCESS	read-only
			STATUS	current
			::= { hmWanMbus54 64 }

hmWanMbus54Value1D		OBJECT-TYPE
			SYNTAX	INTEGER
			MAX-ACCESS	read-only
			STATUS	current
			::= { hmWanMbus54 65 }

hmWanMbus54VIF1E		OBJECT-TYPE
			SYNTAX	INTEGER
			MAX-ACCESS	read-only
			STATUS	current
			::= { hmWanMbus54 66 }

hmWanMbus54Value1E		OBJECT-TYPE
			SYNTAX	INTEGER
			MAX-ACCESS	read-only
			STATUS	current
			::= { hmWanMbus54 67 }

hmWanMbus54VIF1F		OBJECT-TYPE
			SYNTAX	INTEGER
			MAX-ACCESS	read-only
			STATUS	current
			::= { hmWanMbus54 68 }

hmWanMbus54Value1F		OBJECT-TYPE
			SYNTAX	INTEGER
			MAX-ACCESS	read-only
			STATUS	current
			::= { hmWanMbus54 69 }

hmWanMbus54VIF20		OBJECT-TYPE
			SYNTAX	INTEGER
			MAX-ACCESS	read-only
			STATUS	current
			::= { hmWanMbus54 70 }

hmWanMbus54Value20		OBJECT-TYPE
			SYNTAX	INTEGER
			MAX-ACCESS	read-only
			STATUS	current
			::= { hmWanMbus54 71 }

hmWanMbus54VIF21		OBJECT-TYPE
			SYNTAX	INTEGER
			MAX-ACCESS	read-only
			STATUS	current
			::= { hmWanMbus54 72 }

hmWanMbus54Value21		OBJECT-TYPE
			SYNTAX	INTEGER
			MAX-ACCESS	read-only
			STATUS	current
			::= { hmWanMbus54 73 }

hmWanMbus54VIF22		OBJECT-TYPE
			SYNTAX	INTEGER
			MAX-ACCESS	read-only
			STATUS	current
			::= { hmWanMbus54 74 }

hmWanMbus54Value22		OBJECT-TYPE
			SYNTAX	INTEGER
			MAX-ACCESS	read-only
			STATUS	current
			::= { hmWanMbus54 75 }

hmWanMbus54VIF23		OBJECT-TYPE
			SYNTAX	INTEGER
			MAX-ACCESS	read-only
			STATUS	current
			::= { hmWanMbus54 76 }

hmWanMbus54Value23		OBJECT-TYPE
			SYNTAX	INTEGER
			MAX-ACCESS	read-only
			STATUS	current
			::= { hmWanMbus54 77 }

hmWanMbus54VIF24		OBJECT-TYPE
			SYNTAX	INTEGER
			MAX-ACCESS	read-only
			STATUS	current
			::= { hmWanMbus54 78 }

hmWanMbus54Value24		OBJECT-TYPE
			SYNTAX	INTEGER
			MAX-ACCESS	read-only
			STATUS	current
			::= { hmWanMbus54 79 }

hmWanMbus54VIF25		OBJECT-TYPE
			SYNTAX	INTEGER
			MAX-ACCESS	read-only
			STATUS	current
			::= { hmWanMbus54 80 }

hmWanMbus54Value25		OBJECT-TYPE
			SYNTAX	INTEGER
			MAX-ACCESS	read-only
			STATUS	current
			::= { hmWanMbus54 81 }

hmWanMbus54VIF26		OBJECT-TYPE
			SYNTAX	INTEGER
			MAX-ACCESS	read-only
			STATUS	current
			::= { hmWanMbus54 82 }

hmWanMbus54Value26		OBJECT-TYPE
			SYNTAX	INTEGER
			MAX-ACCESS	read-only
			STATUS	current
			::= { hmWanMbus54 83 }

hmWanMbus54VIF27		OBJECT-TYPE
			SYNTAX	INTEGER
			MAX-ACCESS	read-only
			STATUS	current
			::= { hmWanMbus54 84 }

hmWanMbus54Value27		OBJECT-TYPE
			SYNTAX	INTEGER
			MAX-ACCESS	read-only
			STATUS	current
			::= { hmWanMbus54 85 }

hmWanMbus54VIF28		OBJECT-TYPE
			SYNTAX	INTEGER
			MAX-ACCESS	read-only
			STATUS	current
			::= { hmWanMbus54 86 }

hmWanMbus54Value28		OBJECT-TYPE
			SYNTAX	INTEGER
			MAX-ACCESS	read-only
			STATUS	current
			::= { hmWanMbus54 87 }

hmWanMbus54VIF29		OBJECT-TYPE
			SYNTAX	INTEGER
			MAX-ACCESS	read-only
			STATUS	current
			::= { hmWanMbus54 88 }

hmWanMbus54Value29		OBJECT-TYPE
			SYNTAX	INTEGER
			MAX-ACCESS	read-only
			STATUS	current
			::= { hmWanMbus54 89 }

hmWanMbus54VIF2A		OBJECT-TYPE
			SYNTAX	INTEGER
			MAX-ACCESS	read-only
			STATUS	current
			::= { hmWanMbus54 90 }

hmWanMbus54Value2A		OBJECT-TYPE
			SYNTAX	INTEGER
			MAX-ACCESS	read-only
			STATUS	current
			::= { hmWanMbus54 91 }

hmWanMbus54VIF2B		OBJECT-TYPE
			SYNTAX	INTEGER
			MAX-ACCESS	read-only
			STATUS	current
			::= { hmWanMbus54 92 }

hmWanMbus54Value2B		OBJECT-TYPE
			SYNTAX	INTEGER
			MAX-ACCESS	read-only
			STATUS	current
			::= { hmWanMbus54 93 }

hmWanMbus54VIF2C		OBJECT-TYPE
			SYNTAX	INTEGER
			MAX-ACCESS	read-only
			STATUS	current
			::= { hmWanMbus54 94 }

hmWanMbus54Value2C		OBJECT-TYPE
			SYNTAX	INTEGER
			MAX-ACCESS	read-only
			STATUS	current
			::= { hmWanMbus54 95 }

hmWanMbus54VIF2D		OBJECT-TYPE
			SYNTAX	INTEGER
			MAX-ACCESS	read-only
			STATUS	current
			::= { hmWanMbus54 96 }

hmWanMbus54Value2D		OBJECT-TYPE
			SYNTAX	INTEGER
			MAX-ACCESS	read-only
			STATUS	current
			::= { hmWanMbus54 97 }

hmWanMbus54VIF2E		OBJECT-TYPE
			SYNTAX	INTEGER
			MAX-ACCESS	read-only
			STATUS	current
			::= { hmWanMbus54 98 }

hmWanMbus54Value2E		OBJECT-TYPE
			SYNTAX	INTEGER
			MAX-ACCESS	read-only
			STATUS	current
			::= { hmWanMbus54 99 }

hmWanMbus54VIF2F		OBJECT-TYPE
			SYNTAX	INTEGER
			MAX-ACCESS	read-only
			STATUS	current
			::= { hmWanMbus54 100 }

hmWanMbus54Value2F		OBJECT-TYPE
			SYNTAX	INTEGER
			MAX-ACCESS	read-only
			STATUS	current
			::= { hmWanMbus54 101 }

hmWanMbus55			OBJECT IDENTIFIER ::= { hmWanMbus 85 }

hmWanMbus55IdNumber		OBJECT-TYPE
			SYNTAX	Gauge32
			MAX-ACCESS	read-only
			STATUS	current
			::= { hmWanMbus55 1 }

hmWanMbus55Manufacturer	OBJECT-TYPE
			SYNTAX	Gauge32
			MAX-ACCESS	read-only
			STATUS	current
			::= { hmWanMbus55 2 }

hmWanMbus55Version		OBJECT-TYPE
			SYNTAX	Gauge32
			MAX-ACCESS	read-only
			STATUS	current
			::= { hmWanMbus55 3 }

hmWanMbus55Medium		OBJECT-TYPE
			SYNTAX	Gauge32
			MAX-ACCESS	read-only
			STATUS	current
			::= { hmWanMbus55 4 }

hmWanMbus55Status		OBJECT-TYPE
			SYNTAX	Gauge32
			MAX-ACCESS	read-only
			STATUS	current
			::= { hmWanMbus55 5 }

hmWanMbus55VIF00		OBJECT-TYPE
			SYNTAX	INTEGER
			MAX-ACCESS	read-only
			STATUS	current
			::= { hmWanMbus55 6 }

hmWanMbus55Value00		OBJECT-TYPE
			SYNTAX	INTEGER
			MAX-ACCESS	read-only
			STATUS	current
			::= { hmWanMbus55 7 }

hmWanMbus55VIF01		OBJECT-TYPE
			SYNTAX	INTEGER
			MAX-ACCESS	read-only
			STATUS	current
			::= { hmWanMbus55 8 }

hmWanMbus55Value01		OBJECT-TYPE
			SYNTAX	INTEGER
			MAX-ACCESS	read-only
			STATUS	current
			::= { hmWanMbus55 9 }

hmWanMbus55VIF02		OBJECT-TYPE
			SYNTAX	INTEGER
			MAX-ACCESS	read-only
			STATUS	current
			::= { hmWanMbus55 10 }

hmWanMbus55Value02		OBJECT-TYPE
			SYNTAX	INTEGER
			MAX-ACCESS	read-only
			STATUS	current
			::= { hmWanMbus55 11 }

hmWanMbus55VIF03		OBJECT-TYPE
			SYNTAX	INTEGER
			MAX-ACCESS	read-only
			STATUS	current
			::= { hmWanMbus55 12 }

hmWanMbus55Value03		OBJECT-TYPE
			SYNTAX	INTEGER
			MAX-ACCESS	read-only
			STATUS	current
			::= { hmWanMbus55 13 }

hmWanMbus55VIF04		OBJECT-TYPE
			SYNTAX	INTEGER
			MAX-ACCESS	read-only
			STATUS	current
			::= { hmWanMbus55 14 }

hmWanMbus55Value04		OBJECT-TYPE
			SYNTAX	INTEGER
			MAX-ACCESS	read-only
			STATUS	current
			::= { hmWanMbus55 15 }

hmWanMbus55VIF05		OBJECT-TYPE
			SYNTAX	INTEGER
			MAX-ACCESS	read-only
			STATUS	current
			::= { hmWanMbus55 16 }

hmWanMbus55Value05		OBJECT-TYPE
			SYNTAX	INTEGER
			MAX-ACCESS	read-only
			STATUS	current
			::= { hmWanMbus55 17 }

hmWanMbus55VIF06		OBJECT-TYPE
			SYNTAX	INTEGER
			MAX-ACCESS	read-only
			STATUS	current
			::= { hmWanMbus55 18 }

hmWanMbus55Value06		OBJECT-TYPE
			SYNTAX	INTEGER
			MAX-ACCESS	read-only
			STATUS	current
			::= { hmWanMbus55 19 }

hmWanMbus55VIF07		OBJECT-TYPE
			SYNTAX	INTEGER
			MAX-ACCESS	read-only
			STATUS	current
			::= { hmWanMbus55 20 }

hmWanMbus55Value07		OBJECT-TYPE
			SYNTAX	INTEGER
			MAX-ACCESS	read-only
			STATUS	current
			::= { hmWanMbus55 21 }

hmWanMbus55VIF08		OBJECT-TYPE
			SYNTAX	INTEGER
			MAX-ACCESS	read-only
			STATUS	current
			::= { hmWanMbus55 22 }

hmWanMbus55Value08		OBJECT-TYPE
			SYNTAX	INTEGER
			MAX-ACCESS	read-only
			STATUS	current
			::= { hmWanMbus55 23 }

hmWanMbus55VIF09		OBJECT-TYPE
			SYNTAX	INTEGER
			MAX-ACCESS	read-only
			STATUS	current
			::= { hmWanMbus55 24 }

hmWanMbus55Value09		OBJECT-TYPE
			SYNTAX	INTEGER
			MAX-ACCESS	read-only
			STATUS	current
			::= { hmWanMbus55 25 }

hmWanMbus55VIF0A		OBJECT-TYPE
			SYNTAX	INTEGER
			MAX-ACCESS	read-only
			STATUS	current
			::= { hmWanMbus55 26 }

hmWanMbus55Value0A		OBJECT-TYPE
			SYNTAX	INTEGER
			MAX-ACCESS	read-only
			STATUS	current
			::= { hmWanMbus55 27 }

hmWanMbus55VIF0B		OBJECT-TYPE
			SYNTAX	INTEGER
			MAX-ACCESS	read-only
			STATUS	current
			::= { hmWanMbus55 28 }

hmWanMbus55Value0B		OBJECT-TYPE
			SYNTAX	INTEGER
			MAX-ACCESS	read-only
			STATUS	current
			::= { hmWanMbus55 29 }

hmWanMbus55VIF0C		OBJECT-TYPE
			SYNTAX	INTEGER
			MAX-ACCESS	read-only
			STATUS	current
			::= { hmWanMbus55 30 }

hmWanMbus55Value0C		OBJECT-TYPE
			SYNTAX	INTEGER
			MAX-ACCESS	read-only
			STATUS	current
			::= { hmWanMbus55 31 }

hmWanMbus55VIF0D		OBJECT-TYPE
			SYNTAX	INTEGER
			MAX-ACCESS	read-only
			STATUS	current
			::= { hmWanMbus55 32 }

hmWanMbus55Value0D		OBJECT-TYPE
			SYNTAX	INTEGER
			MAX-ACCESS	read-only
			STATUS	current
			::= { hmWanMbus55 33 }

hmWanMbus55VIF0E		OBJECT-TYPE
			SYNTAX	INTEGER
			MAX-ACCESS	read-only
			STATUS	current
			::= { hmWanMbus55 34 }

hmWanMbus55Value0E		OBJECT-TYPE
			SYNTAX	INTEGER
			MAX-ACCESS	read-only
			STATUS	current
			::= { hmWanMbus55 35 }

hmWanMbus55VIF0F		OBJECT-TYPE
			SYNTAX	INTEGER
			MAX-ACCESS	read-only
			STATUS	current
			::= { hmWanMbus55 36 }

hmWanMbus55Value0F		OBJECT-TYPE
			SYNTAX	INTEGER
			MAX-ACCESS	read-only
			STATUS	current
			::= { hmWanMbus55 37 }

hmWanMbus55VIF10		OBJECT-TYPE
			SYNTAX	INTEGER
			MAX-ACCESS	read-only
			STATUS	current
			::= { hmWanMbus55 38 }

hmWanMbus55Value10		OBJECT-TYPE
			SYNTAX	INTEGER
			MAX-ACCESS	read-only
			STATUS	current
			::= { hmWanMbus55 39 }

hmWanMbus55VIF11		OBJECT-TYPE
			SYNTAX	INTEGER
			MAX-ACCESS	read-only
			STATUS	current
			::= { hmWanMbus55 40 }

hmWanMbus55Value11		OBJECT-TYPE
			SYNTAX	INTEGER
			MAX-ACCESS	read-only
			STATUS	current
			::= { hmWanMbus55 41 }

hmWanMbus55VIF12		OBJECT-TYPE
			SYNTAX	INTEGER
			MAX-ACCESS	read-only
			STATUS	current
			::= { hmWanMbus55 42 }

hmWanMbus55Value12		OBJECT-TYPE
			SYNTAX	INTEGER
			MAX-ACCESS	read-only
			STATUS	current
			::= { hmWanMbus55 43 }

hmWanMbus55VIF13		OBJECT-TYPE
			SYNTAX	INTEGER
			MAX-ACCESS	read-only
			STATUS	current
			::= { hmWanMbus55 44 }

hmWanMbus55Value13		OBJECT-TYPE
			SYNTAX	INTEGER
			MAX-ACCESS	read-only
			STATUS	current
			::= { hmWanMbus55 45 }

hmWanMbus55VIF14		OBJECT-TYPE
			SYNTAX	INTEGER
			MAX-ACCESS	read-only
			STATUS	current
			::= { hmWanMbus55 46 }

hmWanMbus55Value14		OBJECT-TYPE
			SYNTAX	INTEGER
			MAX-ACCESS	read-only
			STATUS	current
			::= { hmWanMbus55 47 }

hmWanMbus55VIF15		OBJECT-TYPE
			SYNTAX	INTEGER
			MAX-ACCESS	read-only
			STATUS	current
			::= { hmWanMbus55 48 }

hmWanMbus55Value15		OBJECT-TYPE
			SYNTAX	INTEGER
			MAX-ACCESS	read-only
			STATUS	current
			::= { hmWanMbus55 49 }

hmWanMbus55VIF16		OBJECT-TYPE
			SYNTAX	INTEGER
			MAX-ACCESS	read-only
			STATUS	current
			::= { hmWanMbus55 50 }

hmWanMbus55Value16		OBJECT-TYPE
			SYNTAX	INTEGER
			MAX-ACCESS	read-only
			STATUS	current
			::= { hmWanMbus55 51 }

hmWanMbus55VIF17		OBJECT-TYPE
			SYNTAX	INTEGER
			MAX-ACCESS	read-only
			STATUS	current
			::= { hmWanMbus55 52 }

hmWanMbus55Value17		OBJECT-TYPE
			SYNTAX	INTEGER
			MAX-ACCESS	read-only
			STATUS	current
			::= { hmWanMbus55 53 }

hmWanMbus55VIF18		OBJECT-TYPE
			SYNTAX	INTEGER
			MAX-ACCESS	read-only
			STATUS	current
			::= { hmWanMbus55 54 }

hmWanMbus55Value18		OBJECT-TYPE
			SYNTAX	INTEGER
			MAX-ACCESS	read-only
			STATUS	current
			::= { hmWanMbus55 55 }

hmWanMbus55VIF19		OBJECT-TYPE
			SYNTAX	INTEGER
			MAX-ACCESS	read-only
			STATUS	current
			::= { hmWanMbus55 56 }

hmWanMbus55Value19		OBJECT-TYPE
			SYNTAX	INTEGER
			MAX-ACCESS	read-only
			STATUS	current
			::= { hmWanMbus55 57 }

hmWanMbus55VIF1A		OBJECT-TYPE
			SYNTAX	INTEGER
			MAX-ACCESS	read-only
			STATUS	current
			::= { hmWanMbus55 58 }

hmWanMbus55Value1A		OBJECT-TYPE
			SYNTAX	INTEGER
			MAX-ACCESS	read-only
			STATUS	current
			::= { hmWanMbus55 59 }

hmWanMbus55VIF1B		OBJECT-TYPE
			SYNTAX	INTEGER
			MAX-ACCESS	read-only
			STATUS	current
			::= { hmWanMbus55 60 }

hmWanMbus55Value1B		OBJECT-TYPE
			SYNTAX	INTEGER
			MAX-ACCESS	read-only
			STATUS	current
			::= { hmWanMbus55 61 }

hmWanMbus55VIF1C		OBJECT-TYPE
			SYNTAX	INTEGER
			MAX-ACCESS	read-only
			STATUS	current
			::= { hmWanMbus55 62 }

hmWanMbus55Value1C		OBJECT-TYPE
			SYNTAX	INTEGER
			MAX-ACCESS	read-only
			STATUS	current
			::= { hmWanMbus55 63 }

hmWanMbus55VIF1D		OBJECT-TYPE
			SYNTAX	INTEGER
			MAX-ACCESS	read-only
			STATUS	current
			::= { hmWanMbus55 64 }

hmWanMbus55Value1D		OBJECT-TYPE
			SYNTAX	INTEGER
			MAX-ACCESS	read-only
			STATUS	current
			::= { hmWanMbus55 65 }

hmWanMbus55VIF1E		OBJECT-TYPE
			SYNTAX	INTEGER
			MAX-ACCESS	read-only
			STATUS	current
			::= { hmWanMbus55 66 }

hmWanMbus55Value1E		OBJECT-TYPE
			SYNTAX	INTEGER
			MAX-ACCESS	read-only
			STATUS	current
			::= { hmWanMbus55 67 }

hmWanMbus55VIF1F		OBJECT-TYPE
			SYNTAX	INTEGER
			MAX-ACCESS	read-only
			STATUS	current
			::= { hmWanMbus55 68 }

hmWanMbus55Value1F		OBJECT-TYPE
			SYNTAX	INTEGER
			MAX-ACCESS	read-only
			STATUS	current
			::= { hmWanMbus55 69 }

hmWanMbus55VIF20		OBJECT-TYPE
			SYNTAX	INTEGER
			MAX-ACCESS	read-only
			STATUS	current
			::= { hmWanMbus55 70 }

hmWanMbus55Value20		OBJECT-TYPE
			SYNTAX	INTEGER
			MAX-ACCESS	read-only
			STATUS	current
			::= { hmWanMbus55 71 }

hmWanMbus55VIF21		OBJECT-TYPE
			SYNTAX	INTEGER
			MAX-ACCESS	read-only
			STATUS	current
			::= { hmWanMbus55 72 }

hmWanMbus55Value21		OBJECT-TYPE
			SYNTAX	INTEGER
			MAX-ACCESS	read-only
			STATUS	current
			::= { hmWanMbus55 73 }

hmWanMbus55VIF22		OBJECT-TYPE
			SYNTAX	INTEGER
			MAX-ACCESS	read-only
			STATUS	current
			::= { hmWanMbus55 74 }

hmWanMbus55Value22		OBJECT-TYPE
			SYNTAX	INTEGER
			MAX-ACCESS	read-only
			STATUS	current
			::= { hmWanMbus55 75 }

hmWanMbus55VIF23		OBJECT-TYPE
			SYNTAX	INTEGER
			MAX-ACCESS	read-only
			STATUS	current
			::= { hmWanMbus55 76 }

hmWanMbus55Value23		OBJECT-TYPE
			SYNTAX	INTEGER
			MAX-ACCESS	read-only
			STATUS	current
			::= { hmWanMbus55 77 }

hmWanMbus55VIF24		OBJECT-TYPE
			SYNTAX	INTEGER
			MAX-ACCESS	read-only
			STATUS	current
			::= { hmWanMbus55 78 }

hmWanMbus55Value24		OBJECT-TYPE
			SYNTAX	INTEGER
			MAX-ACCESS	read-only
			STATUS	current
			::= { hmWanMbus55 79 }

hmWanMbus55VIF25		OBJECT-TYPE
			SYNTAX	INTEGER
			MAX-ACCESS	read-only
			STATUS	current
			::= { hmWanMbus55 80 }

hmWanMbus55Value25		OBJECT-TYPE
			SYNTAX	INTEGER
			MAX-ACCESS	read-only
			STATUS	current
			::= { hmWanMbus55 81 }

hmWanMbus55VIF26		OBJECT-TYPE
			SYNTAX	INTEGER
			MAX-ACCESS	read-only
			STATUS	current
			::= { hmWanMbus55 82 }

hmWanMbus55Value26		OBJECT-TYPE
			SYNTAX	INTEGER
			MAX-ACCESS	read-only
			STATUS	current
			::= { hmWanMbus55 83 }

hmWanMbus55VIF27		OBJECT-TYPE
			SYNTAX	INTEGER
			MAX-ACCESS	read-only
			STATUS	current
			::= { hmWanMbus55 84 }

hmWanMbus55Value27		OBJECT-TYPE
			SYNTAX	INTEGER
			MAX-ACCESS	read-only
			STATUS	current
			::= { hmWanMbus55 85 }

hmWanMbus55VIF28		OBJECT-TYPE
			SYNTAX	INTEGER
			MAX-ACCESS	read-only
			STATUS	current
			::= { hmWanMbus55 86 }

hmWanMbus55Value28		OBJECT-TYPE
			SYNTAX	INTEGER
			MAX-ACCESS	read-only
			STATUS	current
			::= { hmWanMbus55 87 }

hmWanMbus55VIF29		OBJECT-TYPE
			SYNTAX	INTEGER
			MAX-ACCESS	read-only
			STATUS	current
			::= { hmWanMbus55 88 }

hmWanMbus55Value29		OBJECT-TYPE
			SYNTAX	INTEGER
			MAX-ACCESS	read-only
			STATUS	current
			::= { hmWanMbus55 89 }

hmWanMbus55VIF2A		OBJECT-TYPE
			SYNTAX	INTEGER
			MAX-ACCESS	read-only
			STATUS	current
			::= { hmWanMbus55 90 }

hmWanMbus55Value2A		OBJECT-TYPE
			SYNTAX	INTEGER
			MAX-ACCESS	read-only
			STATUS	current
			::= { hmWanMbus55 91 }

hmWanMbus55VIF2B		OBJECT-TYPE
			SYNTAX	INTEGER
			MAX-ACCESS	read-only
			STATUS	current
			::= { hmWanMbus55 92 }

hmWanMbus55Value2B		OBJECT-TYPE
			SYNTAX	INTEGER
			MAX-ACCESS	read-only
			STATUS	current
			::= { hmWanMbus55 93 }

hmWanMbus55VIF2C		OBJECT-TYPE
			SYNTAX	INTEGER
			MAX-ACCESS	read-only
			STATUS	current
			::= { hmWanMbus55 94 }

hmWanMbus55Value2C		OBJECT-TYPE
			SYNTAX	INTEGER
			MAX-ACCESS	read-only
			STATUS	current
			::= { hmWanMbus55 95 }

hmWanMbus55VIF2D		OBJECT-TYPE
			SYNTAX	INTEGER
			MAX-ACCESS	read-only
			STATUS	current
			::= { hmWanMbus55 96 }

hmWanMbus55Value2D		OBJECT-TYPE
			SYNTAX	INTEGER
			MAX-ACCESS	read-only
			STATUS	current
			::= { hmWanMbus55 97 }

hmWanMbus55VIF2E		OBJECT-TYPE
			SYNTAX	INTEGER
			MAX-ACCESS	read-only
			STATUS	current
			::= { hmWanMbus55 98 }

hmWanMbus55Value2E		OBJECT-TYPE
			SYNTAX	INTEGER
			MAX-ACCESS	read-only
			STATUS	current
			::= { hmWanMbus55 99 }

hmWanMbus55VIF2F		OBJECT-TYPE
			SYNTAX	INTEGER
			MAX-ACCESS	read-only
			STATUS	current
			::= { hmWanMbus55 100 }

hmWanMbus55Value2F		OBJECT-TYPE
			SYNTAX	INTEGER
			MAX-ACCESS	read-only
			STATUS	current
			::= { hmWanMbus55 101 }

hmWanMbus56			OBJECT IDENTIFIER ::= { hmWanMbus 86 }

hmWanMbus56IdNumber		OBJECT-TYPE
			SYNTAX	Gauge32
			MAX-ACCESS	read-only
			STATUS	current
			::= { hmWanMbus56 1 }

hmWanMbus56Manufacturer	OBJECT-TYPE
			SYNTAX	Gauge32
			MAX-ACCESS	read-only
			STATUS	current
			::= { hmWanMbus56 2 }

hmWanMbus56Version		OBJECT-TYPE
			SYNTAX	Gauge32
			MAX-ACCESS	read-only
			STATUS	current
			::= { hmWanMbus56 3 }

hmWanMbus56Medium		OBJECT-TYPE
			SYNTAX	Gauge32
			MAX-ACCESS	read-only
			STATUS	current
			::= { hmWanMbus56 4 }

hmWanMbus56Status		OBJECT-TYPE
			SYNTAX	Gauge32
			MAX-ACCESS	read-only
			STATUS	current
			::= { hmWanMbus56 5 }

hmWanMbus56VIF00		OBJECT-TYPE
			SYNTAX	INTEGER
			MAX-ACCESS	read-only
			STATUS	current
			::= { hmWanMbus56 6 }

hmWanMbus56Value00		OBJECT-TYPE
			SYNTAX	INTEGER
			MAX-ACCESS	read-only
			STATUS	current
			::= { hmWanMbus56 7 }

hmWanMbus56VIF01		OBJECT-TYPE
			SYNTAX	INTEGER
			MAX-ACCESS	read-only
			STATUS	current
			::= { hmWanMbus56 8 }

hmWanMbus56Value01		OBJECT-TYPE
			SYNTAX	INTEGER
			MAX-ACCESS	read-only
			STATUS	current
			::= { hmWanMbus56 9 }

hmWanMbus56VIF02		OBJECT-TYPE
			SYNTAX	INTEGER
			MAX-ACCESS	read-only
			STATUS	current
			::= { hmWanMbus56 10 }

hmWanMbus56Value02		OBJECT-TYPE
			SYNTAX	INTEGER
			MAX-ACCESS	read-only
			STATUS	current
			::= { hmWanMbus56 11 }

hmWanMbus56VIF03		OBJECT-TYPE
			SYNTAX	INTEGER
			MAX-ACCESS	read-only
			STATUS	current
			::= { hmWanMbus56 12 }

hmWanMbus56Value03		OBJECT-TYPE
			SYNTAX	INTEGER
			MAX-ACCESS	read-only
			STATUS	current
			::= { hmWanMbus56 13 }

hmWanMbus56VIF04		OBJECT-TYPE
			SYNTAX	INTEGER
			MAX-ACCESS	read-only
			STATUS	current
			::= { hmWanMbus56 14 }

hmWanMbus56Value04		OBJECT-TYPE
			SYNTAX	INTEGER
			MAX-ACCESS	read-only
			STATUS	current
			::= { hmWanMbus56 15 }

hmWanMbus56VIF05		OBJECT-TYPE
			SYNTAX	INTEGER
			MAX-ACCESS	read-only
			STATUS	current
			::= { hmWanMbus56 16 }

hmWanMbus56Value05		OBJECT-TYPE
			SYNTAX	INTEGER
			MAX-ACCESS	read-only
			STATUS	current
			::= { hmWanMbus56 17 }

hmWanMbus56VIF06		OBJECT-TYPE
			SYNTAX	INTEGER
			MAX-ACCESS	read-only
			STATUS	current
			::= { hmWanMbus56 18 }

hmWanMbus56Value06		OBJECT-TYPE
			SYNTAX	INTEGER
			MAX-ACCESS	read-only
			STATUS	current
			::= { hmWanMbus56 19 }

hmWanMbus56VIF07		OBJECT-TYPE
			SYNTAX	INTEGER
			MAX-ACCESS	read-only
			STATUS	current
			::= { hmWanMbus56 20 }

hmWanMbus56Value07		OBJECT-TYPE
			SYNTAX	INTEGER
			MAX-ACCESS	read-only
			STATUS	current
			::= { hmWanMbus56 21 }

hmWanMbus56VIF08		OBJECT-TYPE
			SYNTAX	INTEGER
			MAX-ACCESS	read-only
			STATUS	current
			::= { hmWanMbus56 22 }

hmWanMbus56Value08		OBJECT-TYPE
			SYNTAX	INTEGER
			MAX-ACCESS	read-only
			STATUS	current
			::= { hmWanMbus56 23 }

hmWanMbus56VIF09		OBJECT-TYPE
			SYNTAX	INTEGER
			MAX-ACCESS	read-only
			STATUS	current
			::= { hmWanMbus56 24 }

hmWanMbus56Value09		OBJECT-TYPE
			SYNTAX	INTEGER
			MAX-ACCESS	read-only
			STATUS	current
			::= { hmWanMbus56 25 }

hmWanMbus56VIF0A		OBJECT-TYPE
			SYNTAX	INTEGER
			MAX-ACCESS	read-only
			STATUS	current
			::= { hmWanMbus56 26 }

hmWanMbus56Value0A		OBJECT-TYPE
			SYNTAX	INTEGER
			MAX-ACCESS	read-only
			STATUS	current
			::= { hmWanMbus56 27 }

hmWanMbus56VIF0B		OBJECT-TYPE
			SYNTAX	INTEGER
			MAX-ACCESS	read-only
			STATUS	current
			::= { hmWanMbus56 28 }

hmWanMbus56Value0B		OBJECT-TYPE
			SYNTAX	INTEGER
			MAX-ACCESS	read-only
			STATUS	current
			::= { hmWanMbus56 29 }

hmWanMbus56VIF0C		OBJECT-TYPE
			SYNTAX	INTEGER
			MAX-ACCESS	read-only
			STATUS	current
			::= { hmWanMbus56 30 }

hmWanMbus56Value0C		OBJECT-TYPE
			SYNTAX	INTEGER
			MAX-ACCESS	read-only
			STATUS	current
			::= { hmWanMbus56 31 }

hmWanMbus56VIF0D		OBJECT-TYPE
			SYNTAX	INTEGER
			MAX-ACCESS	read-only
			STATUS	current
			::= { hmWanMbus56 32 }

hmWanMbus56Value0D		OBJECT-TYPE
			SYNTAX	INTEGER
			MAX-ACCESS	read-only
			STATUS	current
			::= { hmWanMbus56 33 }

hmWanMbus56VIF0E		OBJECT-TYPE
			SYNTAX	INTEGER
			MAX-ACCESS	read-only
			STATUS	current
			::= { hmWanMbus56 34 }

hmWanMbus56Value0E		OBJECT-TYPE
			SYNTAX	INTEGER
			MAX-ACCESS	read-only
			STATUS	current
			::= { hmWanMbus56 35 }

hmWanMbus56VIF0F		OBJECT-TYPE
			SYNTAX	INTEGER
			MAX-ACCESS	read-only
			STATUS	current
			::= { hmWanMbus56 36 }

hmWanMbus56Value0F		OBJECT-TYPE
			SYNTAX	INTEGER
			MAX-ACCESS	read-only
			STATUS	current
			::= { hmWanMbus56 37 }

hmWanMbus56VIF10		OBJECT-TYPE
			SYNTAX	INTEGER
			MAX-ACCESS	read-only
			STATUS	current
			::= { hmWanMbus56 38 }

hmWanMbus56Value10		OBJECT-TYPE
			SYNTAX	INTEGER
			MAX-ACCESS	read-only
			STATUS	current
			::= { hmWanMbus56 39 }

hmWanMbus56VIF11		OBJECT-TYPE
			SYNTAX	INTEGER
			MAX-ACCESS	read-only
			STATUS	current
			::= { hmWanMbus56 40 }

hmWanMbus56Value11		OBJECT-TYPE
			SYNTAX	INTEGER
			MAX-ACCESS	read-only
			STATUS	current
			::= { hmWanMbus56 41 }

hmWanMbus56VIF12		OBJECT-TYPE
			SYNTAX	INTEGER
			MAX-ACCESS	read-only
			STATUS	current
			::= { hmWanMbus56 42 }

hmWanMbus56Value12		OBJECT-TYPE
			SYNTAX	INTEGER
			MAX-ACCESS	read-only
			STATUS	current
			::= { hmWanMbus56 43 }

hmWanMbus56VIF13		OBJECT-TYPE
			SYNTAX	INTEGER
			MAX-ACCESS	read-only
			STATUS	current
			::= { hmWanMbus56 44 }

hmWanMbus56Value13		OBJECT-TYPE
			SYNTAX	INTEGER
			MAX-ACCESS	read-only
			STATUS	current
			::= { hmWanMbus56 45 }

hmWanMbus56VIF14		OBJECT-TYPE
			SYNTAX	INTEGER
			MAX-ACCESS	read-only
			STATUS	current
			::= { hmWanMbus56 46 }

hmWanMbus56Value14		OBJECT-TYPE
			SYNTAX	INTEGER
			MAX-ACCESS	read-only
			STATUS	current
			::= { hmWanMbus56 47 }

hmWanMbus56VIF15		OBJECT-TYPE
			SYNTAX	INTEGER
			MAX-ACCESS	read-only
			STATUS	current
			::= { hmWanMbus56 48 }

hmWanMbus56Value15		OBJECT-TYPE
			SYNTAX	INTEGER
			MAX-ACCESS	read-only
			STATUS	current
			::= { hmWanMbus56 49 }

hmWanMbus56VIF16		OBJECT-TYPE
			SYNTAX	INTEGER
			MAX-ACCESS	read-only
			STATUS	current
			::= { hmWanMbus56 50 }

hmWanMbus56Value16		OBJECT-TYPE
			SYNTAX	INTEGER
			MAX-ACCESS	read-only
			STATUS	current
			::= { hmWanMbus56 51 }

hmWanMbus56VIF17		OBJECT-TYPE
			SYNTAX	INTEGER
			MAX-ACCESS	read-only
			STATUS	current
			::= { hmWanMbus56 52 }

hmWanMbus56Value17		OBJECT-TYPE
			SYNTAX	INTEGER
			MAX-ACCESS	read-only
			STATUS	current
			::= { hmWanMbus56 53 }

hmWanMbus56VIF18		OBJECT-TYPE
			SYNTAX	INTEGER
			MAX-ACCESS	read-only
			STATUS	current
			::= { hmWanMbus56 54 }

hmWanMbus56Value18		OBJECT-TYPE
			SYNTAX	INTEGER
			MAX-ACCESS	read-only
			STATUS	current
			::= { hmWanMbus56 55 }

hmWanMbus56VIF19		OBJECT-TYPE
			SYNTAX	INTEGER
			MAX-ACCESS	read-only
			STATUS	current
			::= { hmWanMbus56 56 }

hmWanMbus56Value19		OBJECT-TYPE
			SYNTAX	INTEGER
			MAX-ACCESS	read-only
			STATUS	current
			::= { hmWanMbus56 57 }

hmWanMbus56VIF1A		OBJECT-TYPE
			SYNTAX	INTEGER
			MAX-ACCESS	read-only
			STATUS	current
			::= { hmWanMbus56 58 }

hmWanMbus56Value1A		OBJECT-TYPE
			SYNTAX	INTEGER
			MAX-ACCESS	read-only
			STATUS	current
			::= { hmWanMbus56 59 }

hmWanMbus56VIF1B		OBJECT-TYPE
			SYNTAX	INTEGER
			MAX-ACCESS	read-only
			STATUS	current
			::= { hmWanMbus56 60 }

hmWanMbus56Value1B		OBJECT-TYPE
			SYNTAX	INTEGER
			MAX-ACCESS	read-only
			STATUS	current
			::= { hmWanMbus56 61 }

hmWanMbus56VIF1C		OBJECT-TYPE
			SYNTAX	INTEGER
			MAX-ACCESS	read-only
			STATUS	current
			::= { hmWanMbus56 62 }

hmWanMbus56Value1C		OBJECT-TYPE
			SYNTAX	INTEGER
			MAX-ACCESS	read-only
			STATUS	current
			::= { hmWanMbus56 63 }

hmWanMbus56VIF1D		OBJECT-TYPE
			SYNTAX	INTEGER
			MAX-ACCESS	read-only
			STATUS	current
			::= { hmWanMbus56 64 }

hmWanMbus56Value1D		OBJECT-TYPE
			SYNTAX	INTEGER
			MAX-ACCESS	read-only
			STATUS	current
			::= { hmWanMbus56 65 }

hmWanMbus56VIF1E		OBJECT-TYPE
			SYNTAX	INTEGER
			MAX-ACCESS	read-only
			STATUS	current
			::= { hmWanMbus56 66 }

hmWanMbus56Value1E		OBJECT-TYPE
			SYNTAX	INTEGER
			MAX-ACCESS	read-only
			STATUS	current
			::= { hmWanMbus56 67 }

hmWanMbus56VIF1F		OBJECT-TYPE
			SYNTAX	INTEGER
			MAX-ACCESS	read-only
			STATUS	current
			::= { hmWanMbus56 68 }

hmWanMbus56Value1F		OBJECT-TYPE
			SYNTAX	INTEGER
			MAX-ACCESS	read-only
			STATUS	current
			::= { hmWanMbus56 69 }

hmWanMbus56VIF20		OBJECT-TYPE
			SYNTAX	INTEGER
			MAX-ACCESS	read-only
			STATUS	current
			::= { hmWanMbus56 70 }

hmWanMbus56Value20		OBJECT-TYPE
			SYNTAX	INTEGER
			MAX-ACCESS	read-only
			STATUS	current
			::= { hmWanMbus56 71 }

hmWanMbus56VIF21		OBJECT-TYPE
			SYNTAX	INTEGER
			MAX-ACCESS	read-only
			STATUS	current
			::= { hmWanMbus56 72 }

hmWanMbus56Value21		OBJECT-TYPE
			SYNTAX	INTEGER
			MAX-ACCESS	read-only
			STATUS	current
			::= { hmWanMbus56 73 }

hmWanMbus56VIF22		OBJECT-TYPE
			SYNTAX	INTEGER
			MAX-ACCESS	read-only
			STATUS	current
			::= { hmWanMbus56 74 }

hmWanMbus56Value22		OBJECT-TYPE
			SYNTAX	INTEGER
			MAX-ACCESS	read-only
			STATUS	current
			::= { hmWanMbus56 75 }

hmWanMbus56VIF23		OBJECT-TYPE
			SYNTAX	INTEGER
			MAX-ACCESS	read-only
			STATUS	current
			::= { hmWanMbus56 76 }

hmWanMbus56Value23		OBJECT-TYPE
			SYNTAX	INTEGER
			MAX-ACCESS	read-only
			STATUS	current
			::= { hmWanMbus56 77 }

hmWanMbus56VIF24		OBJECT-TYPE
			SYNTAX	INTEGER
			MAX-ACCESS	read-only
			STATUS	current
			::= { hmWanMbus56 78 }

hmWanMbus56Value24		OBJECT-TYPE
			SYNTAX	INTEGER
			MAX-ACCESS	read-only
			STATUS	current
			::= { hmWanMbus56 79 }

hmWanMbus56VIF25		OBJECT-TYPE
			SYNTAX	INTEGER
			MAX-ACCESS	read-only
			STATUS	current
			::= { hmWanMbus56 80 }

hmWanMbus56Value25		OBJECT-TYPE
			SYNTAX	INTEGER
			MAX-ACCESS	read-only
			STATUS	current
			::= { hmWanMbus56 81 }

hmWanMbus56VIF26		OBJECT-TYPE
			SYNTAX	INTEGER
			MAX-ACCESS	read-only
			STATUS	current
			::= { hmWanMbus56 82 }

hmWanMbus56Value26		OBJECT-TYPE
			SYNTAX	INTEGER
			MAX-ACCESS	read-only
			STATUS	current
			::= { hmWanMbus56 83 }

hmWanMbus56VIF27		OBJECT-TYPE
			SYNTAX	INTEGER
			MAX-ACCESS	read-only
			STATUS	current
			::= { hmWanMbus56 84 }

hmWanMbus56Value27		OBJECT-TYPE
			SYNTAX	INTEGER
			MAX-ACCESS	read-only
			STATUS	current
			::= { hmWanMbus56 85 }

hmWanMbus56VIF28		OBJECT-TYPE
			SYNTAX	INTEGER
			MAX-ACCESS	read-only
			STATUS	current
			::= { hmWanMbus56 86 }

hmWanMbus56Value28		OBJECT-TYPE
			SYNTAX	INTEGER
			MAX-ACCESS	read-only
			STATUS	current
			::= { hmWanMbus56 87 }

hmWanMbus56VIF29		OBJECT-TYPE
			SYNTAX	INTEGER
			MAX-ACCESS	read-only
			STATUS	current
			::= { hmWanMbus56 88 }

hmWanMbus56Value29		OBJECT-TYPE
			SYNTAX	INTEGER
			MAX-ACCESS	read-only
			STATUS	current
			::= { hmWanMbus56 89 }

hmWanMbus56VIF2A		OBJECT-TYPE
			SYNTAX	INTEGER
			MAX-ACCESS	read-only
			STATUS	current
			::= { hmWanMbus56 90 }

hmWanMbus56Value2A		OBJECT-TYPE
			SYNTAX	INTEGER
			MAX-ACCESS	read-only
			STATUS	current
			::= { hmWanMbus56 91 }

hmWanMbus56VIF2B		OBJECT-TYPE
			SYNTAX	INTEGER
			MAX-ACCESS	read-only
			STATUS	current
			::= { hmWanMbus56 92 }

hmWanMbus56Value2B		OBJECT-TYPE
			SYNTAX	INTEGER
			MAX-ACCESS	read-only
			STATUS	current
			::= { hmWanMbus56 93 }

hmWanMbus56VIF2C		OBJECT-TYPE
			SYNTAX	INTEGER
			MAX-ACCESS	read-only
			STATUS	current
			::= { hmWanMbus56 94 }

hmWanMbus56Value2C		OBJECT-TYPE
			SYNTAX	INTEGER
			MAX-ACCESS	read-only
			STATUS	current
			::= { hmWanMbus56 95 }

hmWanMbus56VIF2D		OBJECT-TYPE
			SYNTAX	INTEGER
			MAX-ACCESS	read-only
			STATUS	current
			::= { hmWanMbus56 96 }

hmWanMbus56Value2D		OBJECT-TYPE
			SYNTAX	INTEGER
			MAX-ACCESS	read-only
			STATUS	current
			::= { hmWanMbus56 97 }

hmWanMbus56VIF2E		OBJECT-TYPE
			SYNTAX	INTEGER
			MAX-ACCESS	read-only
			STATUS	current
			::= { hmWanMbus56 98 }

hmWanMbus56Value2E		OBJECT-TYPE
			SYNTAX	INTEGER
			MAX-ACCESS	read-only
			STATUS	current
			::= { hmWanMbus56 99 }

hmWanMbus56VIF2F		OBJECT-TYPE
			SYNTAX	INTEGER
			MAX-ACCESS	read-only
			STATUS	current
			::= { hmWanMbus56 100 }

hmWanMbus56Value2F		OBJECT-TYPE
			SYNTAX	INTEGER
			MAX-ACCESS	read-only
			STATUS	current
			::= { hmWanMbus56 101 }

hmWanMbus57			OBJECT IDENTIFIER ::= { hmWanMbus 87 }

hmWanMbus57IdNumber		OBJECT-TYPE
			SYNTAX	Gauge32
			MAX-ACCESS	read-only
			STATUS	current
			::= { hmWanMbus57 1 }

hmWanMbus57Manufacturer	OBJECT-TYPE
			SYNTAX	Gauge32
			MAX-ACCESS	read-only
			STATUS	current
			::= { hmWanMbus57 2 }

hmWanMbus57Version		OBJECT-TYPE
			SYNTAX	Gauge32
			MAX-ACCESS	read-only
			STATUS	current
			::= { hmWanMbus57 3 }

hmWanMbus57Medium		OBJECT-TYPE
			SYNTAX	Gauge32
			MAX-ACCESS	read-only
			STATUS	current
			::= { hmWanMbus57 4 }

hmWanMbus57Status		OBJECT-TYPE
			SYNTAX	Gauge32
			MAX-ACCESS	read-only
			STATUS	current
			::= { hmWanMbus57 5 }

hmWanMbus57VIF00		OBJECT-TYPE
			SYNTAX	INTEGER
			MAX-ACCESS	read-only
			STATUS	current
			::= { hmWanMbus57 6 }

hmWanMbus57Value00		OBJECT-TYPE
			SYNTAX	INTEGER
			MAX-ACCESS	read-only
			STATUS	current
			::= { hmWanMbus57 7 }

hmWanMbus57VIF01		OBJECT-TYPE
			SYNTAX	INTEGER
			MAX-ACCESS	read-only
			STATUS	current
			::= { hmWanMbus57 8 }

hmWanMbus57Value01		OBJECT-TYPE
			SYNTAX	INTEGER
			MAX-ACCESS	read-only
			STATUS	current
			::= { hmWanMbus57 9 }

hmWanMbus57VIF02		OBJECT-TYPE
			SYNTAX	INTEGER
			MAX-ACCESS	read-only
			STATUS	current
			::= { hmWanMbus57 10 }

hmWanMbus57Value02		OBJECT-TYPE
			SYNTAX	INTEGER
			MAX-ACCESS	read-only
			STATUS	current
			::= { hmWanMbus57 11 }

hmWanMbus57VIF03		OBJECT-TYPE
			SYNTAX	INTEGER
			MAX-ACCESS	read-only
			STATUS	current
			::= { hmWanMbus57 12 }

hmWanMbus57Value03		OBJECT-TYPE
			SYNTAX	INTEGER
			MAX-ACCESS	read-only
			STATUS	current
			::= { hmWanMbus57 13 }

hmWanMbus57VIF04		OBJECT-TYPE
			SYNTAX	INTEGER
			MAX-ACCESS	read-only
			STATUS	current
			::= { hmWanMbus57 14 }

hmWanMbus57Value04		OBJECT-TYPE
			SYNTAX	INTEGER
			MAX-ACCESS	read-only
			STATUS	current
			::= { hmWanMbus57 15 }

hmWanMbus57VIF05		OBJECT-TYPE
			SYNTAX	INTEGER
			MAX-ACCESS	read-only
			STATUS	current
			::= { hmWanMbus57 16 }

hmWanMbus57Value05		OBJECT-TYPE
			SYNTAX	INTEGER
			MAX-ACCESS	read-only
			STATUS	current
			::= { hmWanMbus57 17 }

hmWanMbus57VIF06		OBJECT-TYPE
			SYNTAX	INTEGER
			MAX-ACCESS	read-only
			STATUS	current
			::= { hmWanMbus57 18 }

hmWanMbus57Value06		OBJECT-TYPE
			SYNTAX	INTEGER
			MAX-ACCESS	read-only
			STATUS	current
			::= { hmWanMbus57 19 }

hmWanMbus57VIF07		OBJECT-TYPE
			SYNTAX	INTEGER
			MAX-ACCESS	read-only
			STATUS	current
			::= { hmWanMbus57 20 }

hmWanMbus57Value07		OBJECT-TYPE
			SYNTAX	INTEGER
			MAX-ACCESS	read-only
			STATUS	current
			::= { hmWanMbus57 21 }

hmWanMbus57VIF08		OBJECT-TYPE
			SYNTAX	INTEGER
			MAX-ACCESS	read-only
			STATUS	current
			::= { hmWanMbus57 22 }

hmWanMbus57Value08		OBJECT-TYPE
			SYNTAX	INTEGER
			MAX-ACCESS	read-only
			STATUS	current
			::= { hmWanMbus57 23 }

hmWanMbus57VIF09		OBJECT-TYPE
			SYNTAX	INTEGER
			MAX-ACCESS	read-only
			STATUS	current
			::= { hmWanMbus57 24 }

hmWanMbus57Value09		OBJECT-TYPE
			SYNTAX	INTEGER
			MAX-ACCESS	read-only
			STATUS	current
			::= { hmWanMbus57 25 }

hmWanMbus57VIF0A		OBJECT-TYPE
			SYNTAX	INTEGER
			MAX-ACCESS	read-only
			STATUS	current
			::= { hmWanMbus57 26 }

hmWanMbus57Value0A		OBJECT-TYPE
			SYNTAX	INTEGER
			MAX-ACCESS	read-only
			STATUS	current
			::= { hmWanMbus57 27 }

hmWanMbus57VIF0B		OBJECT-TYPE
			SYNTAX	INTEGER
			MAX-ACCESS	read-only
			STATUS	current
			::= { hmWanMbus57 28 }

hmWanMbus57Value0B		OBJECT-TYPE
			SYNTAX	INTEGER
			MAX-ACCESS	read-only
			STATUS	current
			::= { hmWanMbus57 29 }

hmWanMbus57VIF0C		OBJECT-TYPE
			SYNTAX	INTEGER
			MAX-ACCESS	read-only
			STATUS	current
			::= { hmWanMbus57 30 }

hmWanMbus57Value0C		OBJECT-TYPE
			SYNTAX	INTEGER
			MAX-ACCESS	read-only
			STATUS	current
			::= { hmWanMbus57 31 }

hmWanMbus57VIF0D		OBJECT-TYPE
			SYNTAX	INTEGER
			MAX-ACCESS	read-only
			STATUS	current
			::= { hmWanMbus57 32 }

hmWanMbus57Value0D		OBJECT-TYPE
			SYNTAX	INTEGER
			MAX-ACCESS	read-only
			STATUS	current
			::= { hmWanMbus57 33 }

hmWanMbus57VIF0E		OBJECT-TYPE
			SYNTAX	INTEGER
			MAX-ACCESS	read-only
			STATUS	current
			::= { hmWanMbus57 34 }

hmWanMbus57Value0E		OBJECT-TYPE
			SYNTAX	INTEGER
			MAX-ACCESS	read-only
			STATUS	current
			::= { hmWanMbus57 35 }

hmWanMbus57VIF0F		OBJECT-TYPE
			SYNTAX	INTEGER
			MAX-ACCESS	read-only
			STATUS	current
			::= { hmWanMbus57 36 }

hmWanMbus57Value0F		OBJECT-TYPE
			SYNTAX	INTEGER
			MAX-ACCESS	read-only
			STATUS	current
			::= { hmWanMbus57 37 }

hmWanMbus57VIF10		OBJECT-TYPE
			SYNTAX	INTEGER
			MAX-ACCESS	read-only
			STATUS	current
			::= { hmWanMbus57 38 }

hmWanMbus57Value10		OBJECT-TYPE
			SYNTAX	INTEGER
			MAX-ACCESS	read-only
			STATUS	current
			::= { hmWanMbus57 39 }

hmWanMbus57VIF11		OBJECT-TYPE
			SYNTAX	INTEGER
			MAX-ACCESS	read-only
			STATUS	current
			::= { hmWanMbus57 40 }

hmWanMbus57Value11		OBJECT-TYPE
			SYNTAX	INTEGER
			MAX-ACCESS	read-only
			STATUS	current
			::= { hmWanMbus57 41 }

hmWanMbus57VIF12		OBJECT-TYPE
			SYNTAX	INTEGER
			MAX-ACCESS	read-only
			STATUS	current
			::= { hmWanMbus57 42 }

hmWanMbus57Value12		OBJECT-TYPE
			SYNTAX	INTEGER
			MAX-ACCESS	read-only
			STATUS	current
			::= { hmWanMbus57 43 }

hmWanMbus57VIF13		OBJECT-TYPE
			SYNTAX	INTEGER
			MAX-ACCESS	read-only
			STATUS	current
			::= { hmWanMbus57 44 }

hmWanMbus57Value13		OBJECT-TYPE
			SYNTAX	INTEGER
			MAX-ACCESS	read-only
			STATUS	current
			::= { hmWanMbus57 45 }

hmWanMbus57VIF14		OBJECT-TYPE
			SYNTAX	INTEGER
			MAX-ACCESS	read-only
			STATUS	current
			::= { hmWanMbus57 46 }

hmWanMbus57Value14		OBJECT-TYPE
			SYNTAX	INTEGER
			MAX-ACCESS	read-only
			STATUS	current
			::= { hmWanMbus57 47 }

hmWanMbus57VIF15		OBJECT-TYPE
			SYNTAX	INTEGER
			MAX-ACCESS	read-only
			STATUS	current
			::= { hmWanMbus57 48 }

hmWanMbus57Value15		OBJECT-TYPE
			SYNTAX	INTEGER
			MAX-ACCESS	read-only
			STATUS	current
			::= { hmWanMbus57 49 }

hmWanMbus57VIF16		OBJECT-TYPE
			SYNTAX	INTEGER
			MAX-ACCESS	read-only
			STATUS	current
			::= { hmWanMbus57 50 }

hmWanMbus57Value16		OBJECT-TYPE
			SYNTAX	INTEGER
			MAX-ACCESS	read-only
			STATUS	current
			::= { hmWanMbus57 51 }

hmWanMbus57VIF17		OBJECT-TYPE
			SYNTAX	INTEGER
			MAX-ACCESS	read-only
			STATUS	current
			::= { hmWanMbus57 52 }

hmWanMbus57Value17		OBJECT-TYPE
			SYNTAX	INTEGER
			MAX-ACCESS	read-only
			STATUS	current
			::= { hmWanMbus57 53 }

hmWanMbus57VIF18		OBJECT-TYPE
			SYNTAX	INTEGER
			MAX-ACCESS	read-only
			STATUS	current
			::= { hmWanMbus57 54 }

hmWanMbus57Value18		OBJECT-TYPE
			SYNTAX	INTEGER
			MAX-ACCESS	read-only
			STATUS	current
			::= { hmWanMbus57 55 }

hmWanMbus57VIF19		OBJECT-TYPE
			SYNTAX	INTEGER
			MAX-ACCESS	read-only
			STATUS	current
			::= { hmWanMbus57 56 }

hmWanMbus57Value19		OBJECT-TYPE
			SYNTAX	INTEGER
			MAX-ACCESS	read-only
			STATUS	current
			::= { hmWanMbus57 57 }

hmWanMbus57VIF1A		OBJECT-TYPE
			SYNTAX	INTEGER
			MAX-ACCESS	read-only
			STATUS	current
			::= { hmWanMbus57 58 }

hmWanMbus57Value1A		OBJECT-TYPE
			SYNTAX	INTEGER
			MAX-ACCESS	read-only
			STATUS	current
			::= { hmWanMbus57 59 }

hmWanMbus57VIF1B		OBJECT-TYPE
			SYNTAX	INTEGER
			MAX-ACCESS	read-only
			STATUS	current
			::= { hmWanMbus57 60 }

hmWanMbus57Value1B		OBJECT-TYPE
			SYNTAX	INTEGER
			MAX-ACCESS	read-only
			STATUS	current
			::= { hmWanMbus57 61 }

hmWanMbus57VIF1C		OBJECT-TYPE
			SYNTAX	INTEGER
			MAX-ACCESS	read-only
			STATUS	current
			::= { hmWanMbus57 62 }

hmWanMbus57Value1C		OBJECT-TYPE
			SYNTAX	INTEGER
			MAX-ACCESS	read-only
			STATUS	current
			::= { hmWanMbus57 63 }

hmWanMbus57VIF1D		OBJECT-TYPE
			SYNTAX	INTEGER
			MAX-ACCESS	read-only
			STATUS	current
			::= { hmWanMbus57 64 }

hmWanMbus57Value1D		OBJECT-TYPE
			SYNTAX	INTEGER
			MAX-ACCESS	read-only
			STATUS	current
			::= { hmWanMbus57 65 }

hmWanMbus57VIF1E		OBJECT-TYPE
			SYNTAX	INTEGER
			MAX-ACCESS	read-only
			STATUS	current
			::= { hmWanMbus57 66 }

hmWanMbus57Value1E		OBJECT-TYPE
			SYNTAX	INTEGER
			MAX-ACCESS	read-only
			STATUS	current
			::= { hmWanMbus57 67 }

hmWanMbus57VIF1F		OBJECT-TYPE
			SYNTAX	INTEGER
			MAX-ACCESS	read-only
			STATUS	current
			::= { hmWanMbus57 68 }

hmWanMbus57Value1F		OBJECT-TYPE
			SYNTAX	INTEGER
			MAX-ACCESS	read-only
			STATUS	current
			::= { hmWanMbus57 69 }

hmWanMbus57VIF20		OBJECT-TYPE
			SYNTAX	INTEGER
			MAX-ACCESS	read-only
			STATUS	current
			::= { hmWanMbus57 70 }

hmWanMbus57Value20		OBJECT-TYPE
			SYNTAX	INTEGER
			MAX-ACCESS	read-only
			STATUS	current
			::= { hmWanMbus57 71 }

hmWanMbus57VIF21		OBJECT-TYPE
			SYNTAX	INTEGER
			MAX-ACCESS	read-only
			STATUS	current
			::= { hmWanMbus57 72 }

hmWanMbus57Value21		OBJECT-TYPE
			SYNTAX	INTEGER
			MAX-ACCESS	read-only
			STATUS	current
			::= { hmWanMbus57 73 }

hmWanMbus57VIF22		OBJECT-TYPE
			SYNTAX	INTEGER
			MAX-ACCESS	read-only
			STATUS	current
			::= { hmWanMbus57 74 }

hmWanMbus57Value22		OBJECT-TYPE
			SYNTAX	INTEGER
			MAX-ACCESS	read-only
			STATUS	current
			::= { hmWanMbus57 75 }

hmWanMbus57VIF23		OBJECT-TYPE
			SYNTAX	INTEGER
			MAX-ACCESS	read-only
			STATUS	current
			::= { hmWanMbus57 76 }

hmWanMbus57Value23		OBJECT-TYPE
			SYNTAX	INTEGER
			MAX-ACCESS	read-only
			STATUS	current
			::= { hmWanMbus57 77 }

hmWanMbus57VIF24		OBJECT-TYPE
			SYNTAX	INTEGER
			MAX-ACCESS	read-only
			STATUS	current
			::= { hmWanMbus57 78 }

hmWanMbus57Value24		OBJECT-TYPE
			SYNTAX	INTEGER
			MAX-ACCESS	read-only
			STATUS	current
			::= { hmWanMbus57 79 }

hmWanMbus57VIF25		OBJECT-TYPE
			SYNTAX	INTEGER
			MAX-ACCESS	read-only
			STATUS	current
			::= { hmWanMbus57 80 }

hmWanMbus57Value25		OBJECT-TYPE
			SYNTAX	INTEGER
			MAX-ACCESS	read-only
			STATUS	current
			::= { hmWanMbus57 81 }

hmWanMbus57VIF26		OBJECT-TYPE
			SYNTAX	INTEGER
			MAX-ACCESS	read-only
			STATUS	current
			::= { hmWanMbus57 82 }

hmWanMbus57Value26		OBJECT-TYPE
			SYNTAX	INTEGER
			MAX-ACCESS	read-only
			STATUS	current
			::= { hmWanMbus57 83 }

hmWanMbus57VIF27		OBJECT-TYPE
			SYNTAX	INTEGER
			MAX-ACCESS	read-only
			STATUS	current
			::= { hmWanMbus57 84 }

hmWanMbus57Value27		OBJECT-TYPE
			SYNTAX	INTEGER
			MAX-ACCESS	read-only
			STATUS	current
			::= { hmWanMbus57 85 }

hmWanMbus57VIF28		OBJECT-TYPE
			SYNTAX	INTEGER
			MAX-ACCESS	read-only
			STATUS	current
			::= { hmWanMbus57 86 }

hmWanMbus57Value28		OBJECT-TYPE
			SYNTAX	INTEGER
			MAX-ACCESS	read-only
			STATUS	current
			::= { hmWanMbus57 87 }

hmWanMbus57VIF29		OBJECT-TYPE
			SYNTAX	INTEGER
			MAX-ACCESS	read-only
			STATUS	current
			::= { hmWanMbus57 88 }

hmWanMbus57Value29		OBJECT-TYPE
			SYNTAX	INTEGER
			MAX-ACCESS	read-only
			STATUS	current
			::= { hmWanMbus57 89 }

hmWanMbus57VIF2A		OBJECT-TYPE
			SYNTAX	INTEGER
			MAX-ACCESS	read-only
			STATUS	current
			::= { hmWanMbus57 90 }

hmWanMbus57Value2A		OBJECT-TYPE
			SYNTAX	INTEGER
			MAX-ACCESS	read-only
			STATUS	current
			::= { hmWanMbus57 91 }

hmWanMbus57VIF2B		OBJECT-TYPE
			SYNTAX	INTEGER
			MAX-ACCESS	read-only
			STATUS	current
			::= { hmWanMbus57 92 }

hmWanMbus57Value2B		OBJECT-TYPE
			SYNTAX	INTEGER
			MAX-ACCESS	read-only
			STATUS	current
			::= { hmWanMbus57 93 }

hmWanMbus57VIF2C		OBJECT-TYPE
			SYNTAX	INTEGER
			MAX-ACCESS	read-only
			STATUS	current
			::= { hmWanMbus57 94 }

hmWanMbus57Value2C		OBJECT-TYPE
			SYNTAX	INTEGER
			MAX-ACCESS	read-only
			STATUS	current
			::= { hmWanMbus57 95 }

hmWanMbus57VIF2D		OBJECT-TYPE
			SYNTAX	INTEGER
			MAX-ACCESS	read-only
			STATUS	current
			::= { hmWanMbus57 96 }

hmWanMbus57Value2D		OBJECT-TYPE
			SYNTAX	INTEGER
			MAX-ACCESS	read-only
			STATUS	current
			::= { hmWanMbus57 97 }

hmWanMbus57VIF2E		OBJECT-TYPE
			SYNTAX	INTEGER
			MAX-ACCESS	read-only
			STATUS	current
			::= { hmWanMbus57 98 }

hmWanMbus57Value2E		OBJECT-TYPE
			SYNTAX	INTEGER
			MAX-ACCESS	read-only
			STATUS	current
			::= { hmWanMbus57 99 }

hmWanMbus57VIF2F		OBJECT-TYPE
			SYNTAX	INTEGER
			MAX-ACCESS	read-only
			STATUS	current
			::= { hmWanMbus57 100 }

hmWanMbus57Value2F		OBJECT-TYPE
			SYNTAX	INTEGER
			MAX-ACCESS	read-only
			STATUS	current
			::= { hmWanMbus57 101 }

hmWanMbus58			OBJECT IDENTIFIER ::= { hmWanMbus 88 }

hmWanMbus58IdNumber		OBJECT-TYPE
			SYNTAX	Gauge32
			MAX-ACCESS	read-only
			STATUS	current
			::= { hmWanMbus58 1 }

hmWanMbus58Manufacturer	OBJECT-TYPE
			SYNTAX	Gauge32
			MAX-ACCESS	read-only
			STATUS	current
			::= { hmWanMbus58 2 }

hmWanMbus58Version		OBJECT-TYPE
			SYNTAX	Gauge32
			MAX-ACCESS	read-only
			STATUS	current
			::= { hmWanMbus58 3 }

hmWanMbus58Medium		OBJECT-TYPE
			SYNTAX	Gauge32
			MAX-ACCESS	read-only
			STATUS	current
			::= { hmWanMbus58 4 }

hmWanMbus58Status		OBJECT-TYPE
			SYNTAX	Gauge32
			MAX-ACCESS	read-only
			STATUS	current
			::= { hmWanMbus58 5 }

hmWanMbus58VIF00		OBJECT-TYPE
			SYNTAX	INTEGER
			MAX-ACCESS	read-only
			STATUS	current
			::= { hmWanMbus58 6 }

hmWanMbus58Value00		OBJECT-TYPE
			SYNTAX	INTEGER
			MAX-ACCESS	read-only
			STATUS	current
			::= { hmWanMbus58 7 }

hmWanMbus58VIF01		OBJECT-TYPE
			SYNTAX	INTEGER
			MAX-ACCESS	read-only
			STATUS	current
			::= { hmWanMbus58 8 }

hmWanMbus58Value01		OBJECT-TYPE
			SYNTAX	INTEGER
			MAX-ACCESS	read-only
			STATUS	current
			::= { hmWanMbus58 9 }

hmWanMbus58VIF02		OBJECT-TYPE
			SYNTAX	INTEGER
			MAX-ACCESS	read-only
			STATUS	current
			::= { hmWanMbus58 10 }

hmWanMbus58Value02		OBJECT-TYPE
			SYNTAX	INTEGER
			MAX-ACCESS	read-only
			STATUS	current
			::= { hmWanMbus58 11 }

hmWanMbus58VIF03		OBJECT-TYPE
			SYNTAX	INTEGER
			MAX-ACCESS	read-only
			STATUS	current
			::= { hmWanMbus58 12 }

hmWanMbus58Value03		OBJECT-TYPE
			SYNTAX	INTEGER
			MAX-ACCESS	read-only
			STATUS	current
			::= { hmWanMbus58 13 }

hmWanMbus58VIF04		OBJECT-TYPE
			SYNTAX	INTEGER
			MAX-ACCESS	read-only
			STATUS	current
			::= { hmWanMbus58 14 }

hmWanMbus58Value04		OBJECT-TYPE
			SYNTAX	INTEGER
			MAX-ACCESS	read-only
			STATUS	current
			::= { hmWanMbus58 15 }

hmWanMbus58VIF05		OBJECT-TYPE
			SYNTAX	INTEGER
			MAX-ACCESS	read-only
			STATUS	current
			::= { hmWanMbus58 16 }

hmWanMbus58Value05		OBJECT-TYPE
			SYNTAX	INTEGER
			MAX-ACCESS	read-only
			STATUS	current
			::= { hmWanMbus58 17 }

hmWanMbus58VIF06		OBJECT-TYPE
			SYNTAX	INTEGER
			MAX-ACCESS	read-only
			STATUS	current
			::= { hmWanMbus58 18 }

hmWanMbus58Value06		OBJECT-TYPE
			SYNTAX	INTEGER
			MAX-ACCESS	read-only
			STATUS	current
			::= { hmWanMbus58 19 }

hmWanMbus58VIF07		OBJECT-TYPE
			SYNTAX	INTEGER
			MAX-ACCESS	read-only
			STATUS	current
			::= { hmWanMbus58 20 }

hmWanMbus58Value07		OBJECT-TYPE
			SYNTAX	INTEGER
			MAX-ACCESS	read-only
			STATUS	current
			::= { hmWanMbus58 21 }

hmWanMbus58VIF08		OBJECT-TYPE
			SYNTAX	INTEGER
			MAX-ACCESS	read-only
			STATUS	current
			::= { hmWanMbus58 22 }

hmWanMbus58Value08		OBJECT-TYPE
			SYNTAX	INTEGER
			MAX-ACCESS	read-only
			STATUS	current
			::= { hmWanMbus58 23 }

hmWanMbus58VIF09		OBJECT-TYPE
			SYNTAX	INTEGER
			MAX-ACCESS	read-only
			STATUS	current
			::= { hmWanMbus58 24 }

hmWanMbus58Value09		OBJECT-TYPE
			SYNTAX	INTEGER
			MAX-ACCESS	read-only
			STATUS	current
			::= { hmWanMbus58 25 }

hmWanMbus58VIF0A		OBJECT-TYPE
			SYNTAX	INTEGER
			MAX-ACCESS	read-only
			STATUS	current
			::= { hmWanMbus58 26 }

hmWanMbus58Value0A		OBJECT-TYPE
			SYNTAX	INTEGER
			MAX-ACCESS	read-only
			STATUS	current
			::= { hmWanMbus58 27 }

hmWanMbus58VIF0B		OBJECT-TYPE
			SYNTAX	INTEGER
			MAX-ACCESS	read-only
			STATUS	current
			::= { hmWanMbus58 28 }

hmWanMbus58Value0B		OBJECT-TYPE
			SYNTAX	INTEGER
			MAX-ACCESS	read-only
			STATUS	current
			::= { hmWanMbus58 29 }

hmWanMbus58VIF0C		OBJECT-TYPE
			SYNTAX	INTEGER
			MAX-ACCESS	read-only
			STATUS	current
			::= { hmWanMbus58 30 }

hmWanMbus58Value0C		OBJECT-TYPE
			SYNTAX	INTEGER
			MAX-ACCESS	read-only
			STATUS	current
			::= { hmWanMbus58 31 }

hmWanMbus58VIF0D		OBJECT-TYPE
			SYNTAX	INTEGER
			MAX-ACCESS	read-only
			STATUS	current
			::= { hmWanMbus58 32 }

hmWanMbus58Value0D		OBJECT-TYPE
			SYNTAX	INTEGER
			MAX-ACCESS	read-only
			STATUS	current
			::= { hmWanMbus58 33 }

hmWanMbus58VIF0E		OBJECT-TYPE
			SYNTAX	INTEGER
			MAX-ACCESS	read-only
			STATUS	current
			::= { hmWanMbus58 34 }

hmWanMbus58Value0E		OBJECT-TYPE
			SYNTAX	INTEGER
			MAX-ACCESS	read-only
			STATUS	current
			::= { hmWanMbus58 35 }

hmWanMbus58VIF0F		OBJECT-TYPE
			SYNTAX	INTEGER
			MAX-ACCESS	read-only
			STATUS	current
			::= { hmWanMbus58 36 }

hmWanMbus58Value0F		OBJECT-TYPE
			SYNTAX	INTEGER
			MAX-ACCESS	read-only
			STATUS	current
			::= { hmWanMbus58 37 }

hmWanMbus58VIF10		OBJECT-TYPE
			SYNTAX	INTEGER
			MAX-ACCESS	read-only
			STATUS	current
			::= { hmWanMbus58 38 }

hmWanMbus58Value10		OBJECT-TYPE
			SYNTAX	INTEGER
			MAX-ACCESS	read-only
			STATUS	current
			::= { hmWanMbus58 39 }

hmWanMbus58VIF11		OBJECT-TYPE
			SYNTAX	INTEGER
			MAX-ACCESS	read-only
			STATUS	current
			::= { hmWanMbus58 40 }

hmWanMbus58Value11		OBJECT-TYPE
			SYNTAX	INTEGER
			MAX-ACCESS	read-only
			STATUS	current
			::= { hmWanMbus58 41 }

hmWanMbus58VIF12		OBJECT-TYPE
			SYNTAX	INTEGER
			MAX-ACCESS	read-only
			STATUS	current
			::= { hmWanMbus58 42 }

hmWanMbus58Value12		OBJECT-TYPE
			SYNTAX	INTEGER
			MAX-ACCESS	read-only
			STATUS	current
			::= { hmWanMbus58 43 }

hmWanMbus58VIF13		OBJECT-TYPE
			SYNTAX	INTEGER
			MAX-ACCESS	read-only
			STATUS	current
			::= { hmWanMbus58 44 }

hmWanMbus58Value13		OBJECT-TYPE
			SYNTAX	INTEGER
			MAX-ACCESS	read-only
			STATUS	current
			::= { hmWanMbus58 45 }

hmWanMbus58VIF14		OBJECT-TYPE
			SYNTAX	INTEGER
			MAX-ACCESS	read-only
			STATUS	current
			::= { hmWanMbus58 46 }

hmWanMbus58Value14		OBJECT-TYPE
			SYNTAX	INTEGER
			MAX-ACCESS	read-only
			STATUS	current
			::= { hmWanMbus58 47 }

hmWanMbus58VIF15		OBJECT-TYPE
			SYNTAX	INTEGER
			MAX-ACCESS	read-only
			STATUS	current
			::= { hmWanMbus58 48 }

hmWanMbus58Value15		OBJECT-TYPE
			SYNTAX	INTEGER
			MAX-ACCESS	read-only
			STATUS	current
			::= { hmWanMbus58 49 }

hmWanMbus58VIF16		OBJECT-TYPE
			SYNTAX	INTEGER
			MAX-ACCESS	read-only
			STATUS	current
			::= { hmWanMbus58 50 }

hmWanMbus58Value16		OBJECT-TYPE
			SYNTAX	INTEGER
			MAX-ACCESS	read-only
			STATUS	current
			::= { hmWanMbus58 51 }

hmWanMbus58VIF17		OBJECT-TYPE
			SYNTAX	INTEGER
			MAX-ACCESS	read-only
			STATUS	current
			::= { hmWanMbus58 52 }

hmWanMbus58Value17		OBJECT-TYPE
			SYNTAX	INTEGER
			MAX-ACCESS	read-only
			STATUS	current
			::= { hmWanMbus58 53 }

hmWanMbus58VIF18		OBJECT-TYPE
			SYNTAX	INTEGER
			MAX-ACCESS	read-only
			STATUS	current
			::= { hmWanMbus58 54 }

hmWanMbus58Value18		OBJECT-TYPE
			SYNTAX	INTEGER
			MAX-ACCESS	read-only
			STATUS	current
			::= { hmWanMbus58 55 }

hmWanMbus58VIF19		OBJECT-TYPE
			SYNTAX	INTEGER
			MAX-ACCESS	read-only
			STATUS	current
			::= { hmWanMbus58 56 }

hmWanMbus58Value19		OBJECT-TYPE
			SYNTAX	INTEGER
			MAX-ACCESS	read-only
			STATUS	current
			::= { hmWanMbus58 57 }

hmWanMbus58VIF1A		OBJECT-TYPE
			SYNTAX	INTEGER
			MAX-ACCESS	read-only
			STATUS	current
			::= { hmWanMbus58 58 }

hmWanMbus58Value1A		OBJECT-TYPE
			SYNTAX	INTEGER
			MAX-ACCESS	read-only
			STATUS	current
			::= { hmWanMbus58 59 }

hmWanMbus58VIF1B		OBJECT-TYPE
			SYNTAX	INTEGER
			MAX-ACCESS	read-only
			STATUS	current
			::= { hmWanMbus58 60 }

hmWanMbus58Value1B		OBJECT-TYPE
			SYNTAX	INTEGER
			MAX-ACCESS	read-only
			STATUS	current
			::= { hmWanMbus58 61 }

hmWanMbus58VIF1C		OBJECT-TYPE
			SYNTAX	INTEGER
			MAX-ACCESS	read-only
			STATUS	current
			::= { hmWanMbus58 62 }

hmWanMbus58Value1C		OBJECT-TYPE
			SYNTAX	INTEGER
			MAX-ACCESS	read-only
			STATUS	current
			::= { hmWanMbus58 63 }

hmWanMbus58VIF1D		OBJECT-TYPE
			SYNTAX	INTEGER
			MAX-ACCESS	read-only
			STATUS	current
			::= { hmWanMbus58 64 }

hmWanMbus58Value1D		OBJECT-TYPE
			SYNTAX	INTEGER
			MAX-ACCESS	read-only
			STATUS	current
			::= { hmWanMbus58 65 }

hmWanMbus58VIF1E		OBJECT-TYPE
			SYNTAX	INTEGER
			MAX-ACCESS	read-only
			STATUS	current
			::= { hmWanMbus58 66 }

hmWanMbus58Value1E		OBJECT-TYPE
			SYNTAX	INTEGER
			MAX-ACCESS	read-only
			STATUS	current
			::= { hmWanMbus58 67 }

hmWanMbus58VIF1F		OBJECT-TYPE
			SYNTAX	INTEGER
			MAX-ACCESS	read-only
			STATUS	current
			::= { hmWanMbus58 68 }

hmWanMbus58Value1F		OBJECT-TYPE
			SYNTAX	INTEGER
			MAX-ACCESS	read-only
			STATUS	current
			::= { hmWanMbus58 69 }

hmWanMbus58VIF20		OBJECT-TYPE
			SYNTAX	INTEGER
			MAX-ACCESS	read-only
			STATUS	current
			::= { hmWanMbus58 70 }

hmWanMbus58Value20		OBJECT-TYPE
			SYNTAX	INTEGER
			MAX-ACCESS	read-only
			STATUS	current
			::= { hmWanMbus58 71 }

hmWanMbus58VIF21		OBJECT-TYPE
			SYNTAX	INTEGER
			MAX-ACCESS	read-only
			STATUS	current
			::= { hmWanMbus58 72 }

hmWanMbus58Value21		OBJECT-TYPE
			SYNTAX	INTEGER
			MAX-ACCESS	read-only
			STATUS	current
			::= { hmWanMbus58 73 }

hmWanMbus58VIF22		OBJECT-TYPE
			SYNTAX	INTEGER
			MAX-ACCESS	read-only
			STATUS	current
			::= { hmWanMbus58 74 }

hmWanMbus58Value22		OBJECT-TYPE
			SYNTAX	INTEGER
			MAX-ACCESS	read-only
			STATUS	current
			::= { hmWanMbus58 75 }

hmWanMbus58VIF23		OBJECT-TYPE
			SYNTAX	INTEGER
			MAX-ACCESS	read-only
			STATUS	current
			::= { hmWanMbus58 76 }

hmWanMbus58Value23		OBJECT-TYPE
			SYNTAX	INTEGER
			MAX-ACCESS	read-only
			STATUS	current
			::= { hmWanMbus58 77 }

hmWanMbus58VIF24		OBJECT-TYPE
			SYNTAX	INTEGER
			MAX-ACCESS	read-only
			STATUS	current
			::= { hmWanMbus58 78 }

hmWanMbus58Value24		OBJECT-TYPE
			SYNTAX	INTEGER
			MAX-ACCESS	read-only
			STATUS	current
			::= { hmWanMbus58 79 }

hmWanMbus58VIF25		OBJECT-TYPE
			SYNTAX	INTEGER
			MAX-ACCESS	read-only
			STATUS	current
			::= { hmWanMbus58 80 }

hmWanMbus58Value25		OBJECT-TYPE
			SYNTAX	INTEGER
			MAX-ACCESS	read-only
			STATUS	current
			::= { hmWanMbus58 81 }

hmWanMbus58VIF26		OBJECT-TYPE
			SYNTAX	INTEGER
			MAX-ACCESS	read-only
			STATUS	current
			::= { hmWanMbus58 82 }

hmWanMbus58Value26		OBJECT-TYPE
			SYNTAX	INTEGER
			MAX-ACCESS	read-only
			STATUS	current
			::= { hmWanMbus58 83 }

hmWanMbus58VIF27		OBJECT-TYPE
			SYNTAX	INTEGER
			MAX-ACCESS	read-only
			STATUS	current
			::= { hmWanMbus58 84 }

hmWanMbus58Value27		OBJECT-TYPE
			SYNTAX	INTEGER
			MAX-ACCESS	read-only
			STATUS	current
			::= { hmWanMbus58 85 }

hmWanMbus58VIF28		OBJECT-TYPE
			SYNTAX	INTEGER
			MAX-ACCESS	read-only
			STATUS	current
			::= { hmWanMbus58 86 }

hmWanMbus58Value28		OBJECT-TYPE
			SYNTAX	INTEGER
			MAX-ACCESS	read-only
			STATUS	current
			::= { hmWanMbus58 87 }

hmWanMbus58VIF29		OBJECT-TYPE
			SYNTAX	INTEGER
			MAX-ACCESS	read-only
			STATUS	current
			::= { hmWanMbus58 88 }

hmWanMbus58Value29		OBJECT-TYPE
			SYNTAX	INTEGER
			MAX-ACCESS	read-only
			STATUS	current
			::= { hmWanMbus58 89 }

hmWanMbus58VIF2A		OBJECT-TYPE
			SYNTAX	INTEGER
			MAX-ACCESS	read-only
			STATUS	current
			::= { hmWanMbus58 90 }

hmWanMbus58Value2A		OBJECT-TYPE
			SYNTAX	INTEGER
			MAX-ACCESS	read-only
			STATUS	current
			::= { hmWanMbus58 91 }

hmWanMbus58VIF2B		OBJECT-TYPE
			SYNTAX	INTEGER
			MAX-ACCESS	read-only
			STATUS	current
			::= { hmWanMbus58 92 }

hmWanMbus58Value2B		OBJECT-TYPE
			SYNTAX	INTEGER
			MAX-ACCESS	read-only
			STATUS	current
			::= { hmWanMbus58 93 }

hmWanMbus58VIF2C		OBJECT-TYPE
			SYNTAX	INTEGER
			MAX-ACCESS	read-only
			STATUS	current
			::= { hmWanMbus58 94 }

hmWanMbus58Value2C		OBJECT-TYPE
			SYNTAX	INTEGER
			MAX-ACCESS	read-only
			STATUS	current
			::= { hmWanMbus58 95 }

hmWanMbus58VIF2D		OBJECT-TYPE
			SYNTAX	INTEGER
			MAX-ACCESS	read-only
			STATUS	current
			::= { hmWanMbus58 96 }

hmWanMbus58Value2D		OBJECT-TYPE
			SYNTAX	INTEGER
			MAX-ACCESS	read-only
			STATUS	current
			::= { hmWanMbus58 97 }

hmWanMbus58VIF2E		OBJECT-TYPE
			SYNTAX	INTEGER
			MAX-ACCESS	read-only
			STATUS	current
			::= { hmWanMbus58 98 }

hmWanMbus58Value2E		OBJECT-TYPE
			SYNTAX	INTEGER
			MAX-ACCESS	read-only
			STATUS	current
			::= { hmWanMbus58 99 }

hmWanMbus58VIF2F		OBJECT-TYPE
			SYNTAX	INTEGER
			MAX-ACCESS	read-only
			STATUS	current
			::= { hmWanMbus58 100 }

hmWanMbus58Value2F		OBJECT-TYPE
			SYNTAX	INTEGER
			MAX-ACCESS	read-only
			STATUS	current
			::= { hmWanMbus58 101 }

hmWanMbus59			OBJECT IDENTIFIER ::= { hmWanMbus 89 }

hmWanMbus59IdNumber		OBJECT-TYPE
			SYNTAX	Gauge32
			MAX-ACCESS	read-only
			STATUS	current
			::= { hmWanMbus59 1 }

hmWanMbus59Manufacturer	OBJECT-TYPE
			SYNTAX	Gauge32
			MAX-ACCESS	read-only
			STATUS	current
			::= { hmWanMbus59 2 }

hmWanMbus59Version		OBJECT-TYPE
			SYNTAX	Gauge32
			MAX-ACCESS	read-only
			STATUS	current
			::= { hmWanMbus59 3 }

hmWanMbus59Medium		OBJECT-TYPE
			SYNTAX	Gauge32
			MAX-ACCESS	read-only
			STATUS	current
			::= { hmWanMbus59 4 }

hmWanMbus59Status		OBJECT-TYPE
			SYNTAX	Gauge32
			MAX-ACCESS	read-only
			STATUS	current
			::= { hmWanMbus59 5 }

hmWanMbus59VIF00		OBJECT-TYPE
			SYNTAX	INTEGER
			MAX-ACCESS	read-only
			STATUS	current
			::= { hmWanMbus59 6 }

hmWanMbus59Value00		OBJECT-TYPE
			SYNTAX	INTEGER
			MAX-ACCESS	read-only
			STATUS	current
			::= { hmWanMbus59 7 }

hmWanMbus59VIF01		OBJECT-TYPE
			SYNTAX	INTEGER
			MAX-ACCESS	read-only
			STATUS	current
			::= { hmWanMbus59 8 }

hmWanMbus59Value01		OBJECT-TYPE
			SYNTAX	INTEGER
			MAX-ACCESS	read-only
			STATUS	current
			::= { hmWanMbus59 9 }

hmWanMbus59VIF02		OBJECT-TYPE
			SYNTAX	INTEGER
			MAX-ACCESS	read-only
			STATUS	current
			::= { hmWanMbus59 10 }

hmWanMbus59Value02		OBJECT-TYPE
			SYNTAX	INTEGER
			MAX-ACCESS	read-only
			STATUS	current
			::= { hmWanMbus59 11 }

hmWanMbus59VIF03		OBJECT-TYPE
			SYNTAX	INTEGER
			MAX-ACCESS	read-only
			STATUS	current
			::= { hmWanMbus59 12 }

hmWanMbus59Value03		OBJECT-TYPE
			SYNTAX	INTEGER
			MAX-ACCESS	read-only
			STATUS	current
			::= { hmWanMbus59 13 }

hmWanMbus59VIF04		OBJECT-TYPE
			SYNTAX	INTEGER
			MAX-ACCESS	read-only
			STATUS	current
			::= { hmWanMbus59 14 }

hmWanMbus59Value04		OBJECT-TYPE
			SYNTAX	INTEGER
			MAX-ACCESS	read-only
			STATUS	current
			::= { hmWanMbus59 15 }

hmWanMbus59VIF05		OBJECT-TYPE
			SYNTAX	INTEGER
			MAX-ACCESS	read-only
			STATUS	current
			::= { hmWanMbus59 16 }

hmWanMbus59Value05		OBJECT-TYPE
			SYNTAX	INTEGER
			MAX-ACCESS	read-only
			STATUS	current
			::= { hmWanMbus59 17 }

hmWanMbus59VIF06		OBJECT-TYPE
			SYNTAX	INTEGER
			MAX-ACCESS	read-only
			STATUS	current
			::= { hmWanMbus59 18 }

hmWanMbus59Value06		OBJECT-TYPE
			SYNTAX	INTEGER
			MAX-ACCESS	read-only
			STATUS	current
			::= { hmWanMbus59 19 }

hmWanMbus59VIF07		OBJECT-TYPE
			SYNTAX	INTEGER
			MAX-ACCESS	read-only
			STATUS	current
			::= { hmWanMbus59 20 }

hmWanMbus59Value07		OBJECT-TYPE
			SYNTAX	INTEGER
			MAX-ACCESS	read-only
			STATUS	current
			::= { hmWanMbus59 21 }

hmWanMbus59VIF08		OBJECT-TYPE
			SYNTAX	INTEGER
			MAX-ACCESS	read-only
			STATUS	current
			::= { hmWanMbus59 22 }

hmWanMbus59Value08		OBJECT-TYPE
			SYNTAX	INTEGER
			MAX-ACCESS	read-only
			STATUS	current
			::= { hmWanMbus59 23 }

hmWanMbus59VIF09		OBJECT-TYPE
			SYNTAX	INTEGER
			MAX-ACCESS	read-only
			STATUS	current
			::= { hmWanMbus59 24 }

hmWanMbus59Value09		OBJECT-TYPE
			SYNTAX	INTEGER
			MAX-ACCESS	read-only
			STATUS	current
			::= { hmWanMbus59 25 }

hmWanMbus59VIF0A		OBJECT-TYPE
			SYNTAX	INTEGER
			MAX-ACCESS	read-only
			STATUS	current
			::= { hmWanMbus59 26 }

hmWanMbus59Value0A		OBJECT-TYPE
			SYNTAX	INTEGER
			MAX-ACCESS	read-only
			STATUS	current
			::= { hmWanMbus59 27 }

hmWanMbus59VIF0B		OBJECT-TYPE
			SYNTAX	INTEGER
			MAX-ACCESS	read-only
			STATUS	current
			::= { hmWanMbus59 28 }

hmWanMbus59Value0B		OBJECT-TYPE
			SYNTAX	INTEGER
			MAX-ACCESS	read-only
			STATUS	current
			::= { hmWanMbus59 29 }

hmWanMbus59VIF0C		OBJECT-TYPE
			SYNTAX	INTEGER
			MAX-ACCESS	read-only
			STATUS	current
			::= { hmWanMbus59 30 }

hmWanMbus59Value0C		OBJECT-TYPE
			SYNTAX	INTEGER
			MAX-ACCESS	read-only
			STATUS	current
			::= { hmWanMbus59 31 }

hmWanMbus59VIF0D		OBJECT-TYPE
			SYNTAX	INTEGER
			MAX-ACCESS	read-only
			STATUS	current
			::= { hmWanMbus59 32 }

hmWanMbus59Value0D		OBJECT-TYPE
			SYNTAX	INTEGER
			MAX-ACCESS	read-only
			STATUS	current
			::= { hmWanMbus59 33 }

hmWanMbus59VIF0E		OBJECT-TYPE
			SYNTAX	INTEGER
			MAX-ACCESS	read-only
			STATUS	current
			::= { hmWanMbus59 34 }

hmWanMbus59Value0E		OBJECT-TYPE
			SYNTAX	INTEGER
			MAX-ACCESS	read-only
			STATUS	current
			::= { hmWanMbus59 35 }

hmWanMbus59VIF0F		OBJECT-TYPE
			SYNTAX	INTEGER
			MAX-ACCESS	read-only
			STATUS	current
			::= { hmWanMbus59 36 }

hmWanMbus59Value0F		OBJECT-TYPE
			SYNTAX	INTEGER
			MAX-ACCESS	read-only
			STATUS	current
			::= { hmWanMbus59 37 }

hmWanMbus59VIF10		OBJECT-TYPE
			SYNTAX	INTEGER
			MAX-ACCESS	read-only
			STATUS	current
			::= { hmWanMbus59 38 }

hmWanMbus59Value10		OBJECT-TYPE
			SYNTAX	INTEGER
			MAX-ACCESS	read-only
			STATUS	current
			::= { hmWanMbus59 39 }

hmWanMbus59VIF11		OBJECT-TYPE
			SYNTAX	INTEGER
			MAX-ACCESS	read-only
			STATUS	current
			::= { hmWanMbus59 40 }

hmWanMbus59Value11		OBJECT-TYPE
			SYNTAX	INTEGER
			MAX-ACCESS	read-only
			STATUS	current
			::= { hmWanMbus59 41 }

hmWanMbus59VIF12		OBJECT-TYPE
			SYNTAX	INTEGER
			MAX-ACCESS	read-only
			STATUS	current
			::= { hmWanMbus59 42 }

hmWanMbus59Value12		OBJECT-TYPE
			SYNTAX	INTEGER
			MAX-ACCESS	read-only
			STATUS	current
			::= { hmWanMbus59 43 }

hmWanMbus59VIF13		OBJECT-TYPE
			SYNTAX	INTEGER
			MAX-ACCESS	read-only
			STATUS	current
			::= { hmWanMbus59 44 }

hmWanMbus59Value13		OBJECT-TYPE
			SYNTAX	INTEGER
			MAX-ACCESS	read-only
			STATUS	current
			::= { hmWanMbus59 45 }

hmWanMbus59VIF14		OBJECT-TYPE
			SYNTAX	INTEGER
			MAX-ACCESS	read-only
			STATUS	current
			::= { hmWanMbus59 46 }

hmWanMbus59Value14		OBJECT-TYPE
			SYNTAX	INTEGER
			MAX-ACCESS	read-only
			STATUS	current
			::= { hmWanMbus59 47 }

hmWanMbus59VIF15		OBJECT-TYPE
			SYNTAX	INTEGER
			MAX-ACCESS	read-only
			STATUS	current
			::= { hmWanMbus59 48 }

hmWanMbus59Value15		OBJECT-TYPE
			SYNTAX	INTEGER
			MAX-ACCESS	read-only
			STATUS	current
			::= { hmWanMbus59 49 }

hmWanMbus59VIF16		OBJECT-TYPE
			SYNTAX	INTEGER
			MAX-ACCESS	read-only
			STATUS	current
			::= { hmWanMbus59 50 }

hmWanMbus59Value16		OBJECT-TYPE
			SYNTAX	INTEGER
			MAX-ACCESS	read-only
			STATUS	current
			::= { hmWanMbus59 51 }

hmWanMbus59VIF17		OBJECT-TYPE
			SYNTAX	INTEGER
			MAX-ACCESS	read-only
			STATUS	current
			::= { hmWanMbus59 52 }

hmWanMbus59Value17		OBJECT-TYPE
			SYNTAX	INTEGER
			MAX-ACCESS	read-only
			STATUS	current
			::= { hmWanMbus59 53 }

hmWanMbus59VIF18		OBJECT-TYPE
			SYNTAX	INTEGER
			MAX-ACCESS	read-only
			STATUS	current
			::= { hmWanMbus59 54 }

hmWanMbus59Value18		OBJECT-TYPE
			SYNTAX	INTEGER
			MAX-ACCESS	read-only
			STATUS	current
			::= { hmWanMbus59 55 }

hmWanMbus59VIF19		OBJECT-TYPE
			SYNTAX	INTEGER
			MAX-ACCESS	read-only
			STATUS	current
			::= { hmWanMbus59 56 }

hmWanMbus59Value19		OBJECT-TYPE
			SYNTAX	INTEGER
			MAX-ACCESS	read-only
			STATUS	current
			::= { hmWanMbus59 57 }

hmWanMbus59VIF1A		OBJECT-TYPE
			SYNTAX	INTEGER
			MAX-ACCESS	read-only
			STATUS	current
			::= { hmWanMbus59 58 }

hmWanMbus59Value1A		OBJECT-TYPE
			SYNTAX	INTEGER
			MAX-ACCESS	read-only
			STATUS	current
			::= { hmWanMbus59 59 }

hmWanMbus59VIF1B		OBJECT-TYPE
			SYNTAX	INTEGER
			MAX-ACCESS	read-only
			STATUS	current
			::= { hmWanMbus59 60 }

hmWanMbus59Value1B		OBJECT-TYPE
			SYNTAX	INTEGER
			MAX-ACCESS	read-only
			STATUS	current
			::= { hmWanMbus59 61 }

hmWanMbus59VIF1C		OBJECT-TYPE
			SYNTAX	INTEGER
			MAX-ACCESS	read-only
			STATUS	current
			::= { hmWanMbus59 62 }

hmWanMbus59Value1C		OBJECT-TYPE
			SYNTAX	INTEGER
			MAX-ACCESS	read-only
			STATUS	current
			::= { hmWanMbus59 63 }

hmWanMbus59VIF1D		OBJECT-TYPE
			SYNTAX	INTEGER
			MAX-ACCESS	read-only
			STATUS	current
			::= { hmWanMbus59 64 }

hmWanMbus59Value1D		OBJECT-TYPE
			SYNTAX	INTEGER
			MAX-ACCESS	read-only
			STATUS	current
			::= { hmWanMbus59 65 }

hmWanMbus59VIF1E		OBJECT-TYPE
			SYNTAX	INTEGER
			MAX-ACCESS	read-only
			STATUS	current
			::= { hmWanMbus59 66 }

hmWanMbus59Value1E		OBJECT-TYPE
			SYNTAX	INTEGER
			MAX-ACCESS	read-only
			STATUS	current
			::= { hmWanMbus59 67 }

hmWanMbus59VIF1F		OBJECT-TYPE
			SYNTAX	INTEGER
			MAX-ACCESS	read-only
			STATUS	current
			::= { hmWanMbus59 68 }

hmWanMbus59Value1F		OBJECT-TYPE
			SYNTAX	INTEGER
			MAX-ACCESS	read-only
			STATUS	current
			::= { hmWanMbus59 69 }

hmWanMbus59VIF20		OBJECT-TYPE
			SYNTAX	INTEGER
			MAX-ACCESS	read-only
			STATUS	current
			::= { hmWanMbus59 70 }

hmWanMbus59Value20		OBJECT-TYPE
			SYNTAX	INTEGER
			MAX-ACCESS	read-only
			STATUS	current
			::= { hmWanMbus59 71 }

hmWanMbus59VIF21		OBJECT-TYPE
			SYNTAX	INTEGER
			MAX-ACCESS	read-only
			STATUS	current
			::= { hmWanMbus59 72 }

hmWanMbus59Value21		OBJECT-TYPE
			SYNTAX	INTEGER
			MAX-ACCESS	read-only
			STATUS	current
			::= { hmWanMbus59 73 }

hmWanMbus59VIF22		OBJECT-TYPE
			SYNTAX	INTEGER
			MAX-ACCESS	read-only
			STATUS	current
			::= { hmWanMbus59 74 }

hmWanMbus59Value22		OBJECT-TYPE
			SYNTAX	INTEGER
			MAX-ACCESS	read-only
			STATUS	current
			::= { hmWanMbus59 75 }

hmWanMbus59VIF23		OBJECT-TYPE
			SYNTAX	INTEGER
			MAX-ACCESS	read-only
			STATUS	current
			::= { hmWanMbus59 76 }

hmWanMbus59Value23		OBJECT-TYPE
			SYNTAX	INTEGER
			MAX-ACCESS	read-only
			STATUS	current
			::= { hmWanMbus59 77 }

hmWanMbus59VIF24		OBJECT-TYPE
			SYNTAX	INTEGER
			MAX-ACCESS	read-only
			STATUS	current
			::= { hmWanMbus59 78 }

hmWanMbus59Value24		OBJECT-TYPE
			SYNTAX	INTEGER
			MAX-ACCESS	read-only
			STATUS	current
			::= { hmWanMbus59 79 }

hmWanMbus59VIF25		OBJECT-TYPE
			SYNTAX	INTEGER
			MAX-ACCESS	read-only
			STATUS	current
			::= { hmWanMbus59 80 }

hmWanMbus59Value25		OBJECT-TYPE
			SYNTAX	INTEGER
			MAX-ACCESS	read-only
			STATUS	current
			::= { hmWanMbus59 81 }

hmWanMbus59VIF26		OBJECT-TYPE
			SYNTAX	INTEGER
			MAX-ACCESS	read-only
			STATUS	current
			::= { hmWanMbus59 82 }

hmWanMbus59Value26		OBJECT-TYPE
			SYNTAX	INTEGER
			MAX-ACCESS	read-only
			STATUS	current
			::= { hmWanMbus59 83 }

hmWanMbus59VIF27		OBJECT-TYPE
			SYNTAX	INTEGER
			MAX-ACCESS	read-only
			STATUS	current
			::= { hmWanMbus59 84 }

hmWanMbus59Value27		OBJECT-TYPE
			SYNTAX	INTEGER
			MAX-ACCESS	read-only
			STATUS	current
			::= { hmWanMbus59 85 }

hmWanMbus59VIF28		OBJECT-TYPE
			SYNTAX	INTEGER
			MAX-ACCESS	read-only
			STATUS	current
			::= { hmWanMbus59 86 }

hmWanMbus59Value28		OBJECT-TYPE
			SYNTAX	INTEGER
			MAX-ACCESS	read-only
			STATUS	current
			::= { hmWanMbus59 87 }

hmWanMbus59VIF29		OBJECT-TYPE
			SYNTAX	INTEGER
			MAX-ACCESS	read-only
			STATUS	current
			::= { hmWanMbus59 88 }

hmWanMbus59Value29		OBJECT-TYPE
			SYNTAX	INTEGER
			MAX-ACCESS	read-only
			STATUS	current
			::= { hmWanMbus59 89 }

hmWanMbus59VIF2A		OBJECT-TYPE
			SYNTAX	INTEGER
			MAX-ACCESS	read-only
			STATUS	current
			::= { hmWanMbus59 90 }

hmWanMbus59Value2A		OBJECT-TYPE
			SYNTAX	INTEGER
			MAX-ACCESS	read-only
			STATUS	current
			::= { hmWanMbus59 91 }

hmWanMbus59VIF2B		OBJECT-TYPE
			SYNTAX	INTEGER
			MAX-ACCESS	read-only
			STATUS	current
			::= { hmWanMbus59 92 }

hmWanMbus59Value2B		OBJECT-TYPE
			SYNTAX	INTEGER
			MAX-ACCESS	read-only
			STATUS	current
			::= { hmWanMbus59 93 }

hmWanMbus59VIF2C		OBJECT-TYPE
			SYNTAX	INTEGER
			MAX-ACCESS	read-only
			STATUS	current
			::= { hmWanMbus59 94 }

hmWanMbus59Value2C		OBJECT-TYPE
			SYNTAX	INTEGER
			MAX-ACCESS	read-only
			STATUS	current
			::= { hmWanMbus59 95 }

hmWanMbus59VIF2D		OBJECT-TYPE
			SYNTAX	INTEGER
			MAX-ACCESS	read-only
			STATUS	current
			::= { hmWanMbus59 96 }

hmWanMbus59Value2D		OBJECT-TYPE
			SYNTAX	INTEGER
			MAX-ACCESS	read-only
			STATUS	current
			::= { hmWanMbus59 97 }

hmWanMbus59VIF2E		OBJECT-TYPE
			SYNTAX	INTEGER
			MAX-ACCESS	read-only
			STATUS	current
			::= { hmWanMbus59 98 }

hmWanMbus59Value2E		OBJECT-TYPE
			SYNTAX	INTEGER
			MAX-ACCESS	read-only
			STATUS	current
			::= { hmWanMbus59 99 }

hmWanMbus59VIF2F		OBJECT-TYPE
			SYNTAX	INTEGER
			MAX-ACCESS	read-only
			STATUS	current
			::= { hmWanMbus59 100 }

hmWanMbus59Value2F		OBJECT-TYPE
			SYNTAX	INTEGER
			MAX-ACCESS	read-only
			STATUS	current
			::= { hmWanMbus59 101 }

hmWanMbus5A			OBJECT IDENTIFIER ::= { hmWanMbus 90 }

hmWanMbus5AIdNumber		OBJECT-TYPE
			SYNTAX	Gauge32
			MAX-ACCESS	read-only
			STATUS	current
			::= { hmWanMbus5A 1 }

hmWanMbus5AManufacturer	OBJECT-TYPE
			SYNTAX	Gauge32
			MAX-ACCESS	read-only
			STATUS	current
			::= { hmWanMbus5A 2 }

hmWanMbus5AVersion		OBJECT-TYPE
			SYNTAX	Gauge32
			MAX-ACCESS	read-only
			STATUS	current
			::= { hmWanMbus5A 3 }

hmWanMbus5AMedium		OBJECT-TYPE
			SYNTAX	Gauge32
			MAX-ACCESS	read-only
			STATUS	current
			::= { hmWanMbus5A 4 }

hmWanMbus5AStatus		OBJECT-TYPE
			SYNTAX	Gauge32
			MAX-ACCESS	read-only
			STATUS	current
			::= { hmWanMbus5A 5 }

hmWanMbus5AVIF00		OBJECT-TYPE
			SYNTAX	INTEGER
			MAX-ACCESS	read-only
			STATUS	current
			::= { hmWanMbus5A 6 }

hmWanMbus5AValue00		OBJECT-TYPE
			SYNTAX	INTEGER
			MAX-ACCESS	read-only
			STATUS	current
			::= { hmWanMbus5A 7 }

hmWanMbus5AVIF01		OBJECT-TYPE
			SYNTAX	INTEGER
			MAX-ACCESS	read-only
			STATUS	current
			::= { hmWanMbus5A 8 }

hmWanMbus5AValue01		OBJECT-TYPE
			SYNTAX	INTEGER
			MAX-ACCESS	read-only
			STATUS	current
			::= { hmWanMbus5A 9 }

hmWanMbus5AVIF02		OBJECT-TYPE
			SYNTAX	INTEGER
			MAX-ACCESS	read-only
			STATUS	current
			::= { hmWanMbus5A 10 }

hmWanMbus5AValue02		OBJECT-TYPE
			SYNTAX	INTEGER
			MAX-ACCESS	read-only
			STATUS	current
			::= { hmWanMbus5A 11 }

hmWanMbus5AVIF03		OBJECT-TYPE
			SYNTAX	INTEGER
			MAX-ACCESS	read-only
			STATUS	current
			::= { hmWanMbus5A 12 }

hmWanMbus5AValue03		OBJECT-TYPE
			SYNTAX	INTEGER
			MAX-ACCESS	read-only
			STATUS	current
			::= { hmWanMbus5A 13 }

hmWanMbus5AVIF04		OBJECT-TYPE
			SYNTAX	INTEGER
			MAX-ACCESS	read-only
			STATUS	current
			::= { hmWanMbus5A 14 }

hmWanMbus5AValue04		OBJECT-TYPE
			SYNTAX	INTEGER
			MAX-ACCESS	read-only
			STATUS	current
			::= { hmWanMbus5A 15 }

hmWanMbus5AVIF05		OBJECT-TYPE
			SYNTAX	INTEGER
			MAX-ACCESS	read-only
			STATUS	current
			::= { hmWanMbus5A 16 }

hmWanMbus5AValue05		OBJECT-TYPE
			SYNTAX	INTEGER
			MAX-ACCESS	read-only
			STATUS	current
			::= { hmWanMbus5A 17 }

hmWanMbus5AVIF06		OBJECT-TYPE
			SYNTAX	INTEGER
			MAX-ACCESS	read-only
			STATUS	current
			::= { hmWanMbus5A 18 }

hmWanMbus5AValue06		OBJECT-TYPE
			SYNTAX	INTEGER
			MAX-ACCESS	read-only
			STATUS	current
			::= { hmWanMbus5A 19 }

hmWanMbus5AVIF07		OBJECT-TYPE
			SYNTAX	INTEGER
			MAX-ACCESS	read-only
			STATUS	current
			::= { hmWanMbus5A 20 }

hmWanMbus5AValue07		OBJECT-TYPE
			SYNTAX	INTEGER
			MAX-ACCESS	read-only
			STATUS	current
			::= { hmWanMbus5A 21 }

hmWanMbus5AVIF08		OBJECT-TYPE
			SYNTAX	INTEGER
			MAX-ACCESS	read-only
			STATUS	current
			::= { hmWanMbus5A 22 }

hmWanMbus5AValue08		OBJECT-TYPE
			SYNTAX	INTEGER
			MAX-ACCESS	read-only
			STATUS	current
			::= { hmWanMbus5A 23 }

hmWanMbus5AVIF09		OBJECT-TYPE
			SYNTAX	INTEGER
			MAX-ACCESS	read-only
			STATUS	current
			::= { hmWanMbus5A 24 }

hmWanMbus5AValue09		OBJECT-TYPE
			SYNTAX	INTEGER
			MAX-ACCESS	read-only
			STATUS	current
			::= { hmWanMbus5A 25 }

hmWanMbus5AVIF0A		OBJECT-TYPE
			SYNTAX	INTEGER
			MAX-ACCESS	read-only
			STATUS	current
			::= { hmWanMbus5A 26 }

hmWanMbus5AValue0A		OBJECT-TYPE
			SYNTAX	INTEGER
			MAX-ACCESS	read-only
			STATUS	current
			::= { hmWanMbus5A 27 }

hmWanMbus5AVIF0B		OBJECT-TYPE
			SYNTAX	INTEGER
			MAX-ACCESS	read-only
			STATUS	current
			::= { hmWanMbus5A 28 }

hmWanMbus5AValue0B		OBJECT-TYPE
			SYNTAX	INTEGER
			MAX-ACCESS	read-only
			STATUS	current
			::= { hmWanMbus5A 29 }

hmWanMbus5AVIF0C		OBJECT-TYPE
			SYNTAX	INTEGER
			MAX-ACCESS	read-only
			STATUS	current
			::= { hmWanMbus5A 30 }

hmWanMbus5AValue0C		OBJECT-TYPE
			SYNTAX	INTEGER
			MAX-ACCESS	read-only
			STATUS	current
			::= { hmWanMbus5A 31 }

hmWanMbus5AVIF0D		OBJECT-TYPE
			SYNTAX	INTEGER
			MAX-ACCESS	read-only
			STATUS	current
			::= { hmWanMbus5A 32 }

hmWanMbus5AValue0D		OBJECT-TYPE
			SYNTAX	INTEGER
			MAX-ACCESS	read-only
			STATUS	current
			::= { hmWanMbus5A 33 }

hmWanMbus5AVIF0E		OBJECT-TYPE
			SYNTAX	INTEGER
			MAX-ACCESS	read-only
			STATUS	current
			::= { hmWanMbus5A 34 }

hmWanMbus5AValue0E		OBJECT-TYPE
			SYNTAX	INTEGER
			MAX-ACCESS	read-only
			STATUS	current
			::= { hmWanMbus5A 35 }

hmWanMbus5AVIF0F		OBJECT-TYPE
			SYNTAX	INTEGER
			MAX-ACCESS	read-only
			STATUS	current
			::= { hmWanMbus5A 36 }

hmWanMbus5AValue0F		OBJECT-TYPE
			SYNTAX	INTEGER
			MAX-ACCESS	read-only
			STATUS	current
			::= { hmWanMbus5A 37 }

hmWanMbus5AVIF10		OBJECT-TYPE
			SYNTAX	INTEGER
			MAX-ACCESS	read-only
			STATUS	current
			::= { hmWanMbus5A 38 }

hmWanMbus5AValue10		OBJECT-TYPE
			SYNTAX	INTEGER
			MAX-ACCESS	read-only
			STATUS	current
			::= { hmWanMbus5A 39 }

hmWanMbus5AVIF11		OBJECT-TYPE
			SYNTAX	INTEGER
			MAX-ACCESS	read-only
			STATUS	current
			::= { hmWanMbus5A 40 }

hmWanMbus5AValue11		OBJECT-TYPE
			SYNTAX	INTEGER
			MAX-ACCESS	read-only
			STATUS	current
			::= { hmWanMbus5A 41 }

hmWanMbus5AVIF12		OBJECT-TYPE
			SYNTAX	INTEGER
			MAX-ACCESS	read-only
			STATUS	current
			::= { hmWanMbus5A 42 }

hmWanMbus5AValue12		OBJECT-TYPE
			SYNTAX	INTEGER
			MAX-ACCESS	read-only
			STATUS	current
			::= { hmWanMbus5A 43 }

hmWanMbus5AVIF13		OBJECT-TYPE
			SYNTAX	INTEGER
			MAX-ACCESS	read-only
			STATUS	current
			::= { hmWanMbus5A 44 }

hmWanMbus5AValue13		OBJECT-TYPE
			SYNTAX	INTEGER
			MAX-ACCESS	read-only
			STATUS	current
			::= { hmWanMbus5A 45 }

hmWanMbus5AVIF14		OBJECT-TYPE
			SYNTAX	INTEGER
			MAX-ACCESS	read-only
			STATUS	current
			::= { hmWanMbus5A 46 }

hmWanMbus5AValue14		OBJECT-TYPE
			SYNTAX	INTEGER
			MAX-ACCESS	read-only
			STATUS	current
			::= { hmWanMbus5A 47 }

hmWanMbus5AVIF15		OBJECT-TYPE
			SYNTAX	INTEGER
			MAX-ACCESS	read-only
			STATUS	current
			::= { hmWanMbus5A 48 }

hmWanMbus5AValue15		OBJECT-TYPE
			SYNTAX	INTEGER
			MAX-ACCESS	read-only
			STATUS	current
			::= { hmWanMbus5A 49 }

hmWanMbus5AVIF16		OBJECT-TYPE
			SYNTAX	INTEGER
			MAX-ACCESS	read-only
			STATUS	current
			::= { hmWanMbus5A 50 }

hmWanMbus5AValue16		OBJECT-TYPE
			SYNTAX	INTEGER
			MAX-ACCESS	read-only
			STATUS	current
			::= { hmWanMbus5A 51 }

hmWanMbus5AVIF17		OBJECT-TYPE
			SYNTAX	INTEGER
			MAX-ACCESS	read-only
			STATUS	current
			::= { hmWanMbus5A 52 }

hmWanMbus5AValue17		OBJECT-TYPE
			SYNTAX	INTEGER
			MAX-ACCESS	read-only
			STATUS	current
			::= { hmWanMbus5A 53 }

hmWanMbus5AVIF18		OBJECT-TYPE
			SYNTAX	INTEGER
			MAX-ACCESS	read-only
			STATUS	current
			::= { hmWanMbus5A 54 }

hmWanMbus5AValue18		OBJECT-TYPE
			SYNTAX	INTEGER
			MAX-ACCESS	read-only
			STATUS	current
			::= { hmWanMbus5A 55 }

hmWanMbus5AVIF19		OBJECT-TYPE
			SYNTAX	INTEGER
			MAX-ACCESS	read-only
			STATUS	current
			::= { hmWanMbus5A 56 }

hmWanMbus5AValue19		OBJECT-TYPE
			SYNTAX	INTEGER
			MAX-ACCESS	read-only
			STATUS	current
			::= { hmWanMbus5A 57 }

hmWanMbus5AVIF1A		OBJECT-TYPE
			SYNTAX	INTEGER
			MAX-ACCESS	read-only
			STATUS	current
			::= { hmWanMbus5A 58 }

hmWanMbus5AValue1A		OBJECT-TYPE
			SYNTAX	INTEGER
			MAX-ACCESS	read-only
			STATUS	current
			::= { hmWanMbus5A 59 }

hmWanMbus5AVIF1B		OBJECT-TYPE
			SYNTAX	INTEGER
			MAX-ACCESS	read-only
			STATUS	current
			::= { hmWanMbus5A 60 }

hmWanMbus5AValue1B		OBJECT-TYPE
			SYNTAX	INTEGER
			MAX-ACCESS	read-only
			STATUS	current
			::= { hmWanMbus5A 61 }

hmWanMbus5AVIF1C		OBJECT-TYPE
			SYNTAX	INTEGER
			MAX-ACCESS	read-only
			STATUS	current
			::= { hmWanMbus5A 62 }

hmWanMbus5AValue1C		OBJECT-TYPE
			SYNTAX	INTEGER
			MAX-ACCESS	read-only
			STATUS	current
			::= { hmWanMbus5A 63 }

hmWanMbus5AVIF1D		OBJECT-TYPE
			SYNTAX	INTEGER
			MAX-ACCESS	read-only
			STATUS	current
			::= { hmWanMbus5A 64 }

hmWanMbus5AValue1D		OBJECT-TYPE
			SYNTAX	INTEGER
			MAX-ACCESS	read-only
			STATUS	current
			::= { hmWanMbus5A 65 }

hmWanMbus5AVIF1E		OBJECT-TYPE
			SYNTAX	INTEGER
			MAX-ACCESS	read-only
			STATUS	current
			::= { hmWanMbus5A 66 }

hmWanMbus5AValue1E		OBJECT-TYPE
			SYNTAX	INTEGER
			MAX-ACCESS	read-only
			STATUS	current
			::= { hmWanMbus5A 67 }

hmWanMbus5AVIF1F		OBJECT-TYPE
			SYNTAX	INTEGER
			MAX-ACCESS	read-only
			STATUS	current
			::= { hmWanMbus5A 68 }

hmWanMbus5AValue1F		OBJECT-TYPE
			SYNTAX	INTEGER
			MAX-ACCESS	read-only
			STATUS	current
			::= { hmWanMbus5A 69 }

hmWanMbus5AVIF20		OBJECT-TYPE
			SYNTAX	INTEGER
			MAX-ACCESS	read-only
			STATUS	current
			::= { hmWanMbus5A 70 }

hmWanMbus5AValue20		OBJECT-TYPE
			SYNTAX	INTEGER
			MAX-ACCESS	read-only
			STATUS	current
			::= { hmWanMbus5A 71 }

hmWanMbus5AVIF21		OBJECT-TYPE
			SYNTAX	INTEGER
			MAX-ACCESS	read-only
			STATUS	current
			::= { hmWanMbus5A 72 }

hmWanMbus5AValue21		OBJECT-TYPE
			SYNTAX	INTEGER
			MAX-ACCESS	read-only
			STATUS	current
			::= { hmWanMbus5A 73 }

hmWanMbus5AVIF22		OBJECT-TYPE
			SYNTAX	INTEGER
			MAX-ACCESS	read-only
			STATUS	current
			::= { hmWanMbus5A 74 }

hmWanMbus5AValue22		OBJECT-TYPE
			SYNTAX	INTEGER
			MAX-ACCESS	read-only
			STATUS	current
			::= { hmWanMbus5A 75 }

hmWanMbus5AVIF23		OBJECT-TYPE
			SYNTAX	INTEGER
			MAX-ACCESS	read-only
			STATUS	current
			::= { hmWanMbus5A 76 }

hmWanMbus5AValue23		OBJECT-TYPE
			SYNTAX	INTEGER
			MAX-ACCESS	read-only
			STATUS	current
			::= { hmWanMbus5A 77 }

hmWanMbus5AVIF24		OBJECT-TYPE
			SYNTAX	INTEGER
			MAX-ACCESS	read-only
			STATUS	current
			::= { hmWanMbus5A 78 }

hmWanMbus5AValue24		OBJECT-TYPE
			SYNTAX	INTEGER
			MAX-ACCESS	read-only
			STATUS	current
			::= { hmWanMbus5A 79 }

hmWanMbus5AVIF25		OBJECT-TYPE
			SYNTAX	INTEGER
			MAX-ACCESS	read-only
			STATUS	current
			::= { hmWanMbus5A 80 }

hmWanMbus5AValue25		OBJECT-TYPE
			SYNTAX	INTEGER
			MAX-ACCESS	read-only
			STATUS	current
			::= { hmWanMbus5A 81 }

hmWanMbus5AVIF26		OBJECT-TYPE
			SYNTAX	INTEGER
			MAX-ACCESS	read-only
			STATUS	current
			::= { hmWanMbus5A 82 }

hmWanMbus5AValue26		OBJECT-TYPE
			SYNTAX	INTEGER
			MAX-ACCESS	read-only
			STATUS	current
			::= { hmWanMbus5A 83 }

hmWanMbus5AVIF27		OBJECT-TYPE
			SYNTAX	INTEGER
			MAX-ACCESS	read-only
			STATUS	current
			::= { hmWanMbus5A 84 }

hmWanMbus5AValue27		OBJECT-TYPE
			SYNTAX	INTEGER
			MAX-ACCESS	read-only
			STATUS	current
			::= { hmWanMbus5A 85 }

hmWanMbus5AVIF28		OBJECT-TYPE
			SYNTAX	INTEGER
			MAX-ACCESS	read-only
			STATUS	current
			::= { hmWanMbus5A 86 }

hmWanMbus5AValue28		OBJECT-TYPE
			SYNTAX	INTEGER
			MAX-ACCESS	read-only
			STATUS	current
			::= { hmWanMbus5A 87 }

hmWanMbus5AVIF29		OBJECT-TYPE
			SYNTAX	INTEGER
			MAX-ACCESS	read-only
			STATUS	current
			::= { hmWanMbus5A 88 }

hmWanMbus5AValue29		OBJECT-TYPE
			SYNTAX	INTEGER
			MAX-ACCESS	read-only
			STATUS	current
			::= { hmWanMbus5A 89 }

hmWanMbus5AVIF2A		OBJECT-TYPE
			SYNTAX	INTEGER
			MAX-ACCESS	read-only
			STATUS	current
			::= { hmWanMbus5A 90 }

hmWanMbus5AValue2A		OBJECT-TYPE
			SYNTAX	INTEGER
			MAX-ACCESS	read-only
			STATUS	current
			::= { hmWanMbus5A 91 }

hmWanMbus5AVIF2B		OBJECT-TYPE
			SYNTAX	INTEGER
			MAX-ACCESS	read-only
			STATUS	current
			::= { hmWanMbus5A 92 }

hmWanMbus5AValue2B		OBJECT-TYPE
			SYNTAX	INTEGER
			MAX-ACCESS	read-only
			STATUS	current
			::= { hmWanMbus5A 93 }

hmWanMbus5AVIF2C		OBJECT-TYPE
			SYNTAX	INTEGER
			MAX-ACCESS	read-only
			STATUS	current
			::= { hmWanMbus5A 94 }

hmWanMbus5AValue2C		OBJECT-TYPE
			SYNTAX	INTEGER
			MAX-ACCESS	read-only
			STATUS	current
			::= { hmWanMbus5A 95 }

hmWanMbus5AVIF2D		OBJECT-TYPE
			SYNTAX	INTEGER
			MAX-ACCESS	read-only
			STATUS	current
			::= { hmWanMbus5A 96 }

hmWanMbus5AValue2D		OBJECT-TYPE
			SYNTAX	INTEGER
			MAX-ACCESS	read-only
			STATUS	current
			::= { hmWanMbus5A 97 }

hmWanMbus5AVIF2E		OBJECT-TYPE
			SYNTAX	INTEGER
			MAX-ACCESS	read-only
			STATUS	current
			::= { hmWanMbus5A 98 }

hmWanMbus5AValue2E		OBJECT-TYPE
			SYNTAX	INTEGER
			MAX-ACCESS	read-only
			STATUS	current
			::= { hmWanMbus5A 99 }

hmWanMbus5AVIF2F		OBJECT-TYPE
			SYNTAX	INTEGER
			MAX-ACCESS	read-only
			STATUS	current
			::= { hmWanMbus5A 100 }

hmWanMbus5AValue2F		OBJECT-TYPE
			SYNTAX	INTEGER
			MAX-ACCESS	read-only
			STATUS	current
			::= { hmWanMbus5A 101 }

hmWanMbus5B			OBJECT IDENTIFIER ::= { hmWanMbus 91 }

hmWanMbus5BIdNumber		OBJECT-TYPE
			SYNTAX	Gauge32
			MAX-ACCESS	read-only
			STATUS	current
			::= { hmWanMbus5B 1 }

hmWanMbus5BManufacturer	OBJECT-TYPE
			SYNTAX	Gauge32
			MAX-ACCESS	read-only
			STATUS	current
			::= { hmWanMbus5B 2 }

hmWanMbus5BVersion		OBJECT-TYPE
			SYNTAX	Gauge32
			MAX-ACCESS	read-only
			STATUS	current
			::= { hmWanMbus5B 3 }

hmWanMbus5BMedium		OBJECT-TYPE
			SYNTAX	Gauge32
			MAX-ACCESS	read-only
			STATUS	current
			::= { hmWanMbus5B 4 }

hmWanMbus5BStatus		OBJECT-TYPE
			SYNTAX	Gauge32
			MAX-ACCESS	read-only
			STATUS	current
			::= { hmWanMbus5B 5 }

hmWanMbus5BVIF00		OBJECT-TYPE
			SYNTAX	INTEGER
			MAX-ACCESS	read-only
			STATUS	current
			::= { hmWanMbus5B 6 }

hmWanMbus5BValue00		OBJECT-TYPE
			SYNTAX	INTEGER
			MAX-ACCESS	read-only
			STATUS	current
			::= { hmWanMbus5B 7 }

hmWanMbus5BVIF01		OBJECT-TYPE
			SYNTAX	INTEGER
			MAX-ACCESS	read-only
			STATUS	current
			::= { hmWanMbus5B 8 }

hmWanMbus5BValue01		OBJECT-TYPE
			SYNTAX	INTEGER
			MAX-ACCESS	read-only
			STATUS	current
			::= { hmWanMbus5B 9 }

hmWanMbus5BVIF02		OBJECT-TYPE
			SYNTAX	INTEGER
			MAX-ACCESS	read-only
			STATUS	current
			::= { hmWanMbus5B 10 }

hmWanMbus5BValue02		OBJECT-TYPE
			SYNTAX	INTEGER
			MAX-ACCESS	read-only
			STATUS	current
			::= { hmWanMbus5B 11 }

hmWanMbus5BVIF03		OBJECT-TYPE
			SYNTAX	INTEGER
			MAX-ACCESS	read-only
			STATUS	current
			::= { hmWanMbus5B 12 }

hmWanMbus5BValue03		OBJECT-TYPE
			SYNTAX	INTEGER
			MAX-ACCESS	read-only
			STATUS	current
			::= { hmWanMbus5B 13 }

hmWanMbus5BVIF04		OBJECT-TYPE
			SYNTAX	INTEGER
			MAX-ACCESS	read-only
			STATUS	current
			::= { hmWanMbus5B 14 }

hmWanMbus5BValue04		OBJECT-TYPE
			SYNTAX	INTEGER
			MAX-ACCESS	read-only
			STATUS	current
			::= { hmWanMbus5B 15 }

hmWanMbus5BVIF05		OBJECT-TYPE
			SYNTAX	INTEGER
			MAX-ACCESS	read-only
			STATUS	current
			::= { hmWanMbus5B 16 }

hmWanMbus5BValue05		OBJECT-TYPE
			SYNTAX	INTEGER
			MAX-ACCESS	read-only
			STATUS	current
			::= { hmWanMbus5B 17 }

hmWanMbus5BVIF06		OBJECT-TYPE
			SYNTAX	INTEGER
			MAX-ACCESS	read-only
			STATUS	current
			::= { hmWanMbus5B 18 }

hmWanMbus5BValue06		OBJECT-TYPE
			SYNTAX	INTEGER
			MAX-ACCESS	read-only
			STATUS	current
			::= { hmWanMbus5B 19 }

hmWanMbus5BVIF07		OBJECT-TYPE
			SYNTAX	INTEGER
			MAX-ACCESS	read-only
			STATUS	current
			::= { hmWanMbus5B 20 }

hmWanMbus5BValue07		OBJECT-TYPE
			SYNTAX	INTEGER
			MAX-ACCESS	read-only
			STATUS	current
			::= { hmWanMbus5B 21 }

hmWanMbus5BVIF08		OBJECT-TYPE
			SYNTAX	INTEGER
			MAX-ACCESS	read-only
			STATUS	current
			::= { hmWanMbus5B 22 }

hmWanMbus5BValue08		OBJECT-TYPE
			SYNTAX	INTEGER
			MAX-ACCESS	read-only
			STATUS	current
			::= { hmWanMbus5B 23 }

hmWanMbus5BVIF09		OBJECT-TYPE
			SYNTAX	INTEGER
			MAX-ACCESS	read-only
			STATUS	current
			::= { hmWanMbus5B 24 }

hmWanMbus5BValue09		OBJECT-TYPE
			SYNTAX	INTEGER
			MAX-ACCESS	read-only
			STATUS	current
			::= { hmWanMbus5B 25 }

hmWanMbus5BVIF0A		OBJECT-TYPE
			SYNTAX	INTEGER
			MAX-ACCESS	read-only
			STATUS	current
			::= { hmWanMbus5B 26 }

hmWanMbus5BValue0A		OBJECT-TYPE
			SYNTAX	INTEGER
			MAX-ACCESS	read-only
			STATUS	current
			::= { hmWanMbus5B 27 }

hmWanMbus5BVIF0B		OBJECT-TYPE
			SYNTAX	INTEGER
			MAX-ACCESS	read-only
			STATUS	current
			::= { hmWanMbus5B 28 }

hmWanMbus5BValue0B		OBJECT-TYPE
			SYNTAX	INTEGER
			MAX-ACCESS	read-only
			STATUS	current
			::= { hmWanMbus5B 29 }

hmWanMbus5BVIF0C		OBJECT-TYPE
			SYNTAX	INTEGER
			MAX-ACCESS	read-only
			STATUS	current
			::= { hmWanMbus5B 30 }

hmWanMbus5BValue0C		OBJECT-TYPE
			SYNTAX	INTEGER
			MAX-ACCESS	read-only
			STATUS	current
			::= { hmWanMbus5B 31 }

hmWanMbus5BVIF0D		OBJECT-TYPE
			SYNTAX	INTEGER
			MAX-ACCESS	read-only
			STATUS	current
			::= { hmWanMbus5B 32 }

hmWanMbus5BValue0D		OBJECT-TYPE
			SYNTAX	INTEGER
			MAX-ACCESS	read-only
			STATUS	current
			::= { hmWanMbus5B 33 }

hmWanMbus5BVIF0E		OBJECT-TYPE
			SYNTAX	INTEGER
			MAX-ACCESS	read-only
			STATUS	current
			::= { hmWanMbus5B 34 }

hmWanMbus5BValue0E		OBJECT-TYPE
			SYNTAX	INTEGER
			MAX-ACCESS	read-only
			STATUS	current
			::= { hmWanMbus5B 35 }

hmWanMbus5BVIF0F		OBJECT-TYPE
			SYNTAX	INTEGER
			MAX-ACCESS	read-only
			STATUS	current
			::= { hmWanMbus5B 36 }

hmWanMbus5BValue0F		OBJECT-TYPE
			SYNTAX	INTEGER
			MAX-ACCESS	read-only
			STATUS	current
			::= { hmWanMbus5B 37 }

hmWanMbus5BVIF10		OBJECT-TYPE
			SYNTAX	INTEGER
			MAX-ACCESS	read-only
			STATUS	current
			::= { hmWanMbus5B 38 }

hmWanMbus5BValue10		OBJECT-TYPE
			SYNTAX	INTEGER
			MAX-ACCESS	read-only
			STATUS	current
			::= { hmWanMbus5B 39 }

hmWanMbus5BVIF11		OBJECT-TYPE
			SYNTAX	INTEGER
			MAX-ACCESS	read-only
			STATUS	current
			::= { hmWanMbus5B 40 }

hmWanMbus5BValue11		OBJECT-TYPE
			SYNTAX	INTEGER
			MAX-ACCESS	read-only
			STATUS	current
			::= { hmWanMbus5B 41 }

hmWanMbus5BVIF12		OBJECT-TYPE
			SYNTAX	INTEGER
			MAX-ACCESS	read-only
			STATUS	current
			::= { hmWanMbus5B 42 }

hmWanMbus5BValue12		OBJECT-TYPE
			SYNTAX	INTEGER
			MAX-ACCESS	read-only
			STATUS	current
			::= { hmWanMbus5B 43 }

hmWanMbus5BVIF13		OBJECT-TYPE
			SYNTAX	INTEGER
			MAX-ACCESS	read-only
			STATUS	current
			::= { hmWanMbus5B 44 }

hmWanMbus5BValue13		OBJECT-TYPE
			SYNTAX	INTEGER
			MAX-ACCESS	read-only
			STATUS	current
			::= { hmWanMbus5B 45 }

hmWanMbus5BVIF14		OBJECT-TYPE
			SYNTAX	INTEGER
			MAX-ACCESS	read-only
			STATUS	current
			::= { hmWanMbus5B 46 }

hmWanMbus5BValue14		OBJECT-TYPE
			SYNTAX	INTEGER
			MAX-ACCESS	read-only
			STATUS	current
			::= { hmWanMbus5B 47 }

hmWanMbus5BVIF15		OBJECT-TYPE
			SYNTAX	INTEGER
			MAX-ACCESS	read-only
			STATUS	current
			::= { hmWanMbus5B 48 }

hmWanMbus5BValue15		OBJECT-TYPE
			SYNTAX	INTEGER
			MAX-ACCESS	read-only
			STATUS	current
			::= { hmWanMbus5B 49 }

hmWanMbus5BVIF16		OBJECT-TYPE
			SYNTAX	INTEGER
			MAX-ACCESS	read-only
			STATUS	current
			::= { hmWanMbus5B 50 }

hmWanMbus5BValue16		OBJECT-TYPE
			SYNTAX	INTEGER
			MAX-ACCESS	read-only
			STATUS	current
			::= { hmWanMbus5B 51 }

hmWanMbus5BVIF17		OBJECT-TYPE
			SYNTAX	INTEGER
			MAX-ACCESS	read-only
			STATUS	current
			::= { hmWanMbus5B 52 }

hmWanMbus5BValue17		OBJECT-TYPE
			SYNTAX	INTEGER
			MAX-ACCESS	read-only
			STATUS	current
			::= { hmWanMbus5B 53 }

hmWanMbus5BVIF18		OBJECT-TYPE
			SYNTAX	INTEGER
			MAX-ACCESS	read-only
			STATUS	current
			::= { hmWanMbus5B 54 }

hmWanMbus5BValue18		OBJECT-TYPE
			SYNTAX	INTEGER
			MAX-ACCESS	read-only
			STATUS	current
			::= { hmWanMbus5B 55 }

hmWanMbus5BVIF19		OBJECT-TYPE
			SYNTAX	INTEGER
			MAX-ACCESS	read-only
			STATUS	current
			::= { hmWanMbus5B 56 }

hmWanMbus5BValue19		OBJECT-TYPE
			SYNTAX	INTEGER
			MAX-ACCESS	read-only
			STATUS	current
			::= { hmWanMbus5B 57 }

hmWanMbus5BVIF1A		OBJECT-TYPE
			SYNTAX	INTEGER
			MAX-ACCESS	read-only
			STATUS	current
			::= { hmWanMbus5B 58 }

hmWanMbus5BValue1A		OBJECT-TYPE
			SYNTAX	INTEGER
			MAX-ACCESS	read-only
			STATUS	current
			::= { hmWanMbus5B 59 }

hmWanMbus5BVIF1B		OBJECT-TYPE
			SYNTAX	INTEGER
			MAX-ACCESS	read-only
			STATUS	current
			::= { hmWanMbus5B 60 }

hmWanMbus5BValue1B		OBJECT-TYPE
			SYNTAX	INTEGER
			MAX-ACCESS	read-only
			STATUS	current
			::= { hmWanMbus5B 61 }

hmWanMbus5BVIF1C		OBJECT-TYPE
			SYNTAX	INTEGER
			MAX-ACCESS	read-only
			STATUS	current
			::= { hmWanMbus5B 62 }

hmWanMbus5BValue1C		OBJECT-TYPE
			SYNTAX	INTEGER
			MAX-ACCESS	read-only
			STATUS	current
			::= { hmWanMbus5B 63 }

hmWanMbus5BVIF1D		OBJECT-TYPE
			SYNTAX	INTEGER
			MAX-ACCESS	read-only
			STATUS	current
			::= { hmWanMbus5B 64 }

hmWanMbus5BValue1D		OBJECT-TYPE
			SYNTAX	INTEGER
			MAX-ACCESS	read-only
			STATUS	current
			::= { hmWanMbus5B 65 }

hmWanMbus5BVIF1E		OBJECT-TYPE
			SYNTAX	INTEGER
			MAX-ACCESS	read-only
			STATUS	current
			::= { hmWanMbus5B 66 }

hmWanMbus5BValue1E		OBJECT-TYPE
			SYNTAX	INTEGER
			MAX-ACCESS	read-only
			STATUS	current
			::= { hmWanMbus5B 67 }

hmWanMbus5BVIF1F		OBJECT-TYPE
			SYNTAX	INTEGER
			MAX-ACCESS	read-only
			STATUS	current
			::= { hmWanMbus5B 68 }

hmWanMbus5BValue1F		OBJECT-TYPE
			SYNTAX	INTEGER
			MAX-ACCESS	read-only
			STATUS	current
			::= { hmWanMbus5B 69 }

hmWanMbus5BVIF20		OBJECT-TYPE
			SYNTAX	INTEGER
			MAX-ACCESS	read-only
			STATUS	current
			::= { hmWanMbus5B 70 }

hmWanMbus5BValue20		OBJECT-TYPE
			SYNTAX	INTEGER
			MAX-ACCESS	read-only
			STATUS	current
			::= { hmWanMbus5B 71 }

hmWanMbus5BVIF21		OBJECT-TYPE
			SYNTAX	INTEGER
			MAX-ACCESS	read-only
			STATUS	current
			::= { hmWanMbus5B 72 }

hmWanMbus5BValue21		OBJECT-TYPE
			SYNTAX	INTEGER
			MAX-ACCESS	read-only
			STATUS	current
			::= { hmWanMbus5B 73 }

hmWanMbus5BVIF22		OBJECT-TYPE
			SYNTAX	INTEGER
			MAX-ACCESS	read-only
			STATUS	current
			::= { hmWanMbus5B 74 }

hmWanMbus5BValue22		OBJECT-TYPE
			SYNTAX	INTEGER
			MAX-ACCESS	read-only
			STATUS	current
			::= { hmWanMbus5B 75 }

hmWanMbus5BVIF23		OBJECT-TYPE
			SYNTAX	INTEGER
			MAX-ACCESS	read-only
			STATUS	current
			::= { hmWanMbus5B 76 }

hmWanMbus5BValue23		OBJECT-TYPE
			SYNTAX	INTEGER
			MAX-ACCESS	read-only
			STATUS	current
			::= { hmWanMbus5B 77 }

hmWanMbus5BVIF24		OBJECT-TYPE
			SYNTAX	INTEGER
			MAX-ACCESS	read-only
			STATUS	current
			::= { hmWanMbus5B 78 }

hmWanMbus5BValue24		OBJECT-TYPE
			SYNTAX	INTEGER
			MAX-ACCESS	read-only
			STATUS	current
			::= { hmWanMbus5B 79 }

hmWanMbus5BVIF25		OBJECT-TYPE
			SYNTAX	INTEGER
			MAX-ACCESS	read-only
			STATUS	current
			::= { hmWanMbus5B 80 }

hmWanMbus5BValue25		OBJECT-TYPE
			SYNTAX	INTEGER
			MAX-ACCESS	read-only
			STATUS	current
			::= { hmWanMbus5B 81 }

hmWanMbus5BVIF26		OBJECT-TYPE
			SYNTAX	INTEGER
			MAX-ACCESS	read-only
			STATUS	current
			::= { hmWanMbus5B 82 }

hmWanMbus5BValue26		OBJECT-TYPE
			SYNTAX	INTEGER
			MAX-ACCESS	read-only
			STATUS	current
			::= { hmWanMbus5B 83 }

hmWanMbus5BVIF27		OBJECT-TYPE
			SYNTAX	INTEGER
			MAX-ACCESS	read-only
			STATUS	current
			::= { hmWanMbus5B 84 }

hmWanMbus5BValue27		OBJECT-TYPE
			SYNTAX	INTEGER
			MAX-ACCESS	read-only
			STATUS	current
			::= { hmWanMbus5B 85 }

hmWanMbus5BVIF28		OBJECT-TYPE
			SYNTAX	INTEGER
			MAX-ACCESS	read-only
			STATUS	current
			::= { hmWanMbus5B 86 }

hmWanMbus5BValue28		OBJECT-TYPE
			SYNTAX	INTEGER
			MAX-ACCESS	read-only
			STATUS	current
			::= { hmWanMbus5B 87 }

hmWanMbus5BVIF29		OBJECT-TYPE
			SYNTAX	INTEGER
			MAX-ACCESS	read-only
			STATUS	current
			::= { hmWanMbus5B 88 }

hmWanMbus5BValue29		OBJECT-TYPE
			SYNTAX	INTEGER
			MAX-ACCESS	read-only
			STATUS	current
			::= { hmWanMbus5B 89 }

hmWanMbus5BVIF2A		OBJECT-TYPE
			SYNTAX	INTEGER
			MAX-ACCESS	read-only
			STATUS	current
			::= { hmWanMbus5B 90 }

hmWanMbus5BValue2A		OBJECT-TYPE
			SYNTAX	INTEGER
			MAX-ACCESS	read-only
			STATUS	current
			::= { hmWanMbus5B 91 }

hmWanMbus5BVIF2B		OBJECT-TYPE
			SYNTAX	INTEGER
			MAX-ACCESS	read-only
			STATUS	current
			::= { hmWanMbus5B 92 }

hmWanMbus5BValue2B		OBJECT-TYPE
			SYNTAX	INTEGER
			MAX-ACCESS	read-only
			STATUS	current
			::= { hmWanMbus5B 93 }

hmWanMbus5BVIF2C		OBJECT-TYPE
			SYNTAX	INTEGER
			MAX-ACCESS	read-only
			STATUS	current
			::= { hmWanMbus5B 94 }

hmWanMbus5BValue2C		OBJECT-TYPE
			SYNTAX	INTEGER
			MAX-ACCESS	read-only
			STATUS	current
			::= { hmWanMbus5B 95 }

hmWanMbus5BVIF2D		OBJECT-TYPE
			SYNTAX	INTEGER
			MAX-ACCESS	read-only
			STATUS	current
			::= { hmWanMbus5B 96 }

hmWanMbus5BValue2D		OBJECT-TYPE
			SYNTAX	INTEGER
			MAX-ACCESS	read-only
			STATUS	current
			::= { hmWanMbus5B 97 }

hmWanMbus5BVIF2E		OBJECT-TYPE
			SYNTAX	INTEGER
			MAX-ACCESS	read-only
			STATUS	current
			::= { hmWanMbus5B 98 }

hmWanMbus5BValue2E		OBJECT-TYPE
			SYNTAX	INTEGER
			MAX-ACCESS	read-only
			STATUS	current
			::= { hmWanMbus5B 99 }

hmWanMbus5BVIF2F		OBJECT-TYPE
			SYNTAX	INTEGER
			MAX-ACCESS	read-only
			STATUS	current
			::= { hmWanMbus5B 100 }

hmWanMbus5BValue2F		OBJECT-TYPE
			SYNTAX	INTEGER
			MAX-ACCESS	read-only
			STATUS	current
			::= { hmWanMbus5B 101 }

hmWanMbus5C			OBJECT IDENTIFIER ::= { hmWanMbus 92 }

hmWanMbus5CIdNumber		OBJECT-TYPE
			SYNTAX	Gauge32
			MAX-ACCESS	read-only
			STATUS	current
			::= { hmWanMbus5C 1 }

hmWanMbus5CManufacturer	OBJECT-TYPE
			SYNTAX	Gauge32
			MAX-ACCESS	read-only
			STATUS	current
			::= { hmWanMbus5C 2 }

hmWanMbus5CVersion		OBJECT-TYPE
			SYNTAX	Gauge32
			MAX-ACCESS	read-only
			STATUS	current
			::= { hmWanMbus5C 3 }

hmWanMbus5CMedium		OBJECT-TYPE
			SYNTAX	Gauge32
			MAX-ACCESS	read-only
			STATUS	current
			::= { hmWanMbus5C 4 }

hmWanMbus5CStatus		OBJECT-TYPE
			SYNTAX	Gauge32
			MAX-ACCESS	read-only
			STATUS	current
			::= { hmWanMbus5C 5 }

hmWanMbus5CVIF00		OBJECT-TYPE
			SYNTAX	INTEGER
			MAX-ACCESS	read-only
			STATUS	current
			::= { hmWanMbus5C 6 }

hmWanMbus5CValue00		OBJECT-TYPE
			SYNTAX	INTEGER
			MAX-ACCESS	read-only
			STATUS	current
			::= { hmWanMbus5C 7 }

hmWanMbus5CVIF01		OBJECT-TYPE
			SYNTAX	INTEGER
			MAX-ACCESS	read-only
			STATUS	current
			::= { hmWanMbus5C 8 }

hmWanMbus5CValue01		OBJECT-TYPE
			SYNTAX	INTEGER
			MAX-ACCESS	read-only
			STATUS	current
			::= { hmWanMbus5C 9 }

hmWanMbus5CVIF02		OBJECT-TYPE
			SYNTAX	INTEGER
			MAX-ACCESS	read-only
			STATUS	current
			::= { hmWanMbus5C 10 }

hmWanMbus5CValue02		OBJECT-TYPE
			SYNTAX	INTEGER
			MAX-ACCESS	read-only
			STATUS	current
			::= { hmWanMbus5C 11 }

hmWanMbus5CVIF03		OBJECT-TYPE
			SYNTAX	INTEGER
			MAX-ACCESS	read-only
			STATUS	current
			::= { hmWanMbus5C 12 }

hmWanMbus5CValue03		OBJECT-TYPE
			SYNTAX	INTEGER
			MAX-ACCESS	read-only
			STATUS	current
			::= { hmWanMbus5C 13 }

hmWanMbus5CVIF04		OBJECT-TYPE
			SYNTAX	INTEGER
			MAX-ACCESS	read-only
			STATUS	current
			::= { hmWanMbus5C 14 }

hmWanMbus5CValue04		OBJECT-TYPE
			SYNTAX	INTEGER
			MAX-ACCESS	read-only
			STATUS	current
			::= { hmWanMbus5C 15 }

hmWanMbus5CVIF05		OBJECT-TYPE
			SYNTAX	INTEGER
			MAX-ACCESS	read-only
			STATUS	current
			::= { hmWanMbus5C 16 }

hmWanMbus5CValue05		OBJECT-TYPE
			SYNTAX	INTEGER
			MAX-ACCESS	read-only
			STATUS	current
			::= { hmWanMbus5C 17 }

hmWanMbus5CVIF06		OBJECT-TYPE
			SYNTAX	INTEGER
			MAX-ACCESS	read-only
			STATUS	current
			::= { hmWanMbus5C 18 }

hmWanMbus5CValue06		OBJECT-TYPE
			SYNTAX	INTEGER
			MAX-ACCESS	read-only
			STATUS	current
			::= { hmWanMbus5C 19 }

hmWanMbus5CVIF07		OBJECT-TYPE
			SYNTAX	INTEGER
			MAX-ACCESS	read-only
			STATUS	current
			::= { hmWanMbus5C 20 }

hmWanMbus5CValue07		OBJECT-TYPE
			SYNTAX	INTEGER
			MAX-ACCESS	read-only
			STATUS	current
			::= { hmWanMbus5C 21 }

hmWanMbus5CVIF08		OBJECT-TYPE
			SYNTAX	INTEGER
			MAX-ACCESS	read-only
			STATUS	current
			::= { hmWanMbus5C 22 }

hmWanMbus5CValue08		OBJECT-TYPE
			SYNTAX	INTEGER
			MAX-ACCESS	read-only
			STATUS	current
			::= { hmWanMbus5C 23 }

hmWanMbus5CVIF09		OBJECT-TYPE
			SYNTAX	INTEGER
			MAX-ACCESS	read-only
			STATUS	current
			::= { hmWanMbus5C 24 }

hmWanMbus5CValue09		OBJECT-TYPE
			SYNTAX	INTEGER
			MAX-ACCESS	read-only
			STATUS	current
			::= { hmWanMbus5C 25 }

hmWanMbus5CVIF0A		OBJECT-TYPE
			SYNTAX	INTEGER
			MAX-ACCESS	read-only
			STATUS	current
			::= { hmWanMbus5C 26 }

hmWanMbus5CValue0A		OBJECT-TYPE
			SYNTAX	INTEGER
			MAX-ACCESS	read-only
			STATUS	current
			::= { hmWanMbus5C 27 }

hmWanMbus5CVIF0B		OBJECT-TYPE
			SYNTAX	INTEGER
			MAX-ACCESS	read-only
			STATUS	current
			::= { hmWanMbus5C 28 }

hmWanMbus5CValue0B		OBJECT-TYPE
			SYNTAX	INTEGER
			MAX-ACCESS	read-only
			STATUS	current
			::= { hmWanMbus5C 29 }

hmWanMbus5CVIF0C		OBJECT-TYPE
			SYNTAX	INTEGER
			MAX-ACCESS	read-only
			STATUS	current
			::= { hmWanMbus5C 30 }

hmWanMbus5CValue0C		OBJECT-TYPE
			SYNTAX	INTEGER
			MAX-ACCESS	read-only
			STATUS	current
			::= { hmWanMbus5C 31 }

hmWanMbus5CVIF0D		OBJECT-TYPE
			SYNTAX	INTEGER
			MAX-ACCESS	read-only
			STATUS	current
			::= { hmWanMbus5C 32 }

hmWanMbus5CValue0D		OBJECT-TYPE
			SYNTAX	INTEGER
			MAX-ACCESS	read-only
			STATUS	current
			::= { hmWanMbus5C 33 }

hmWanMbus5CVIF0E		OBJECT-TYPE
			SYNTAX	INTEGER
			MAX-ACCESS	read-only
			STATUS	current
			::= { hmWanMbus5C 34 }

hmWanMbus5CValue0E		OBJECT-TYPE
			SYNTAX	INTEGER
			MAX-ACCESS	read-only
			STATUS	current
			::= { hmWanMbus5C 35 }

hmWanMbus5CVIF0F		OBJECT-TYPE
			SYNTAX	INTEGER
			MAX-ACCESS	read-only
			STATUS	current
			::= { hmWanMbus5C 36 }

hmWanMbus5CValue0F		OBJECT-TYPE
			SYNTAX	INTEGER
			MAX-ACCESS	read-only
			STATUS	current
			::= { hmWanMbus5C 37 }

hmWanMbus5CVIF10		OBJECT-TYPE
			SYNTAX	INTEGER
			MAX-ACCESS	read-only
			STATUS	current
			::= { hmWanMbus5C 38 }

hmWanMbus5CValue10		OBJECT-TYPE
			SYNTAX	INTEGER
			MAX-ACCESS	read-only
			STATUS	current
			::= { hmWanMbus5C 39 }

hmWanMbus5CVIF11		OBJECT-TYPE
			SYNTAX	INTEGER
			MAX-ACCESS	read-only
			STATUS	current
			::= { hmWanMbus5C 40 }

hmWanMbus5CValue11		OBJECT-TYPE
			SYNTAX	INTEGER
			MAX-ACCESS	read-only
			STATUS	current
			::= { hmWanMbus5C 41 }

hmWanMbus5CVIF12		OBJECT-TYPE
			SYNTAX	INTEGER
			MAX-ACCESS	read-only
			STATUS	current
			::= { hmWanMbus5C 42 }

hmWanMbus5CValue12		OBJECT-TYPE
			SYNTAX	INTEGER
			MAX-ACCESS	read-only
			STATUS	current
			::= { hmWanMbus5C 43 }

hmWanMbus5CVIF13		OBJECT-TYPE
			SYNTAX	INTEGER
			MAX-ACCESS	read-only
			STATUS	current
			::= { hmWanMbus5C 44 }

hmWanMbus5CValue13		OBJECT-TYPE
			SYNTAX	INTEGER
			MAX-ACCESS	read-only
			STATUS	current
			::= { hmWanMbus5C 45 }

hmWanMbus5CVIF14		OBJECT-TYPE
			SYNTAX	INTEGER
			MAX-ACCESS	read-only
			STATUS	current
			::= { hmWanMbus5C 46 }

hmWanMbus5CValue14		OBJECT-TYPE
			SYNTAX	INTEGER
			MAX-ACCESS	read-only
			STATUS	current
			::= { hmWanMbus5C 47 }

hmWanMbus5CVIF15		OBJECT-TYPE
			SYNTAX	INTEGER
			MAX-ACCESS	read-only
			STATUS	current
			::= { hmWanMbus5C 48 }

hmWanMbus5CValue15		OBJECT-TYPE
			SYNTAX	INTEGER
			MAX-ACCESS	read-only
			STATUS	current
			::= { hmWanMbus5C 49 }

hmWanMbus5CVIF16		OBJECT-TYPE
			SYNTAX	INTEGER
			MAX-ACCESS	read-only
			STATUS	current
			::= { hmWanMbus5C 50 }

hmWanMbus5CValue16		OBJECT-TYPE
			SYNTAX	INTEGER
			MAX-ACCESS	read-only
			STATUS	current
			::= { hmWanMbus5C 51 }

hmWanMbus5CVIF17		OBJECT-TYPE
			SYNTAX	INTEGER
			MAX-ACCESS	read-only
			STATUS	current
			::= { hmWanMbus5C 52 }

hmWanMbus5CValue17		OBJECT-TYPE
			SYNTAX	INTEGER
			MAX-ACCESS	read-only
			STATUS	current
			::= { hmWanMbus5C 53 }

hmWanMbus5CVIF18		OBJECT-TYPE
			SYNTAX	INTEGER
			MAX-ACCESS	read-only
			STATUS	current
			::= { hmWanMbus5C 54 }

hmWanMbus5CValue18		OBJECT-TYPE
			SYNTAX	INTEGER
			MAX-ACCESS	read-only
			STATUS	current
			::= { hmWanMbus5C 55 }

hmWanMbus5CVIF19		OBJECT-TYPE
			SYNTAX	INTEGER
			MAX-ACCESS	read-only
			STATUS	current
			::= { hmWanMbus5C 56 }

hmWanMbus5CValue19		OBJECT-TYPE
			SYNTAX	INTEGER
			MAX-ACCESS	read-only
			STATUS	current
			::= { hmWanMbus5C 57 }

hmWanMbus5CVIF1A		OBJECT-TYPE
			SYNTAX	INTEGER
			MAX-ACCESS	read-only
			STATUS	current
			::= { hmWanMbus5C 58 }

hmWanMbus5CValue1A		OBJECT-TYPE
			SYNTAX	INTEGER
			MAX-ACCESS	read-only
			STATUS	current
			::= { hmWanMbus5C 59 }

hmWanMbus5CVIF1B		OBJECT-TYPE
			SYNTAX	INTEGER
			MAX-ACCESS	read-only
			STATUS	current
			::= { hmWanMbus5C 60 }

hmWanMbus5CValue1B		OBJECT-TYPE
			SYNTAX	INTEGER
			MAX-ACCESS	read-only
			STATUS	current
			::= { hmWanMbus5C 61 }

hmWanMbus5CVIF1C		OBJECT-TYPE
			SYNTAX	INTEGER
			MAX-ACCESS	read-only
			STATUS	current
			::= { hmWanMbus5C 62 }

hmWanMbus5CValue1C		OBJECT-TYPE
			SYNTAX	INTEGER
			MAX-ACCESS	read-only
			STATUS	current
			::= { hmWanMbus5C 63 }

hmWanMbus5CVIF1D		OBJECT-TYPE
			SYNTAX	INTEGER
			MAX-ACCESS	read-only
			STATUS	current
			::= { hmWanMbus5C 64 }

hmWanMbus5CValue1D		OBJECT-TYPE
			SYNTAX	INTEGER
			MAX-ACCESS	read-only
			STATUS	current
			::= { hmWanMbus5C 65 }

hmWanMbus5CVIF1E		OBJECT-TYPE
			SYNTAX	INTEGER
			MAX-ACCESS	read-only
			STATUS	current
			::= { hmWanMbus5C 66 }

hmWanMbus5CValue1E		OBJECT-TYPE
			SYNTAX	INTEGER
			MAX-ACCESS	read-only
			STATUS	current
			::= { hmWanMbus5C 67 }

hmWanMbus5CVIF1F		OBJECT-TYPE
			SYNTAX	INTEGER
			MAX-ACCESS	read-only
			STATUS	current
			::= { hmWanMbus5C 68 }

hmWanMbus5CValue1F		OBJECT-TYPE
			SYNTAX	INTEGER
			MAX-ACCESS	read-only
			STATUS	current
			::= { hmWanMbus5C 69 }

hmWanMbus5CVIF20		OBJECT-TYPE
			SYNTAX	INTEGER
			MAX-ACCESS	read-only
			STATUS	current
			::= { hmWanMbus5C 70 }

hmWanMbus5CValue20		OBJECT-TYPE
			SYNTAX	INTEGER
			MAX-ACCESS	read-only
			STATUS	current
			::= { hmWanMbus5C 71 }

hmWanMbus5CVIF21		OBJECT-TYPE
			SYNTAX	INTEGER
			MAX-ACCESS	read-only
			STATUS	current
			::= { hmWanMbus5C 72 }

hmWanMbus5CValue21		OBJECT-TYPE
			SYNTAX	INTEGER
			MAX-ACCESS	read-only
			STATUS	current
			::= { hmWanMbus5C 73 }

hmWanMbus5CVIF22		OBJECT-TYPE
			SYNTAX	INTEGER
			MAX-ACCESS	read-only
			STATUS	current
			::= { hmWanMbus5C 74 }

hmWanMbus5CValue22		OBJECT-TYPE
			SYNTAX	INTEGER
			MAX-ACCESS	read-only
			STATUS	current
			::= { hmWanMbus5C 75 }

hmWanMbus5CVIF23		OBJECT-TYPE
			SYNTAX	INTEGER
			MAX-ACCESS	read-only
			STATUS	current
			::= { hmWanMbus5C 76 }

hmWanMbus5CValue23		OBJECT-TYPE
			SYNTAX	INTEGER
			MAX-ACCESS	read-only
			STATUS	current
			::= { hmWanMbus5C 77 }

hmWanMbus5CVIF24		OBJECT-TYPE
			SYNTAX	INTEGER
			MAX-ACCESS	read-only
			STATUS	current
			::= { hmWanMbus5C 78 }

hmWanMbus5CValue24		OBJECT-TYPE
			SYNTAX	INTEGER
			MAX-ACCESS	read-only
			STATUS	current
			::= { hmWanMbus5C 79 }

hmWanMbus5CVIF25		OBJECT-TYPE
			SYNTAX	INTEGER
			MAX-ACCESS	read-only
			STATUS	current
			::= { hmWanMbus5C 80 }

hmWanMbus5CValue25		OBJECT-TYPE
			SYNTAX	INTEGER
			MAX-ACCESS	read-only
			STATUS	current
			::= { hmWanMbus5C 81 }

hmWanMbus5CVIF26		OBJECT-TYPE
			SYNTAX	INTEGER
			MAX-ACCESS	read-only
			STATUS	current
			::= { hmWanMbus5C 82 }

hmWanMbus5CValue26		OBJECT-TYPE
			SYNTAX	INTEGER
			MAX-ACCESS	read-only
			STATUS	current
			::= { hmWanMbus5C 83 }

hmWanMbus5CVIF27		OBJECT-TYPE
			SYNTAX	INTEGER
			MAX-ACCESS	read-only
			STATUS	current
			::= { hmWanMbus5C 84 }

hmWanMbus5CValue27		OBJECT-TYPE
			SYNTAX	INTEGER
			MAX-ACCESS	read-only
			STATUS	current
			::= { hmWanMbus5C 85 }

hmWanMbus5CVIF28		OBJECT-TYPE
			SYNTAX	INTEGER
			MAX-ACCESS	read-only
			STATUS	current
			::= { hmWanMbus5C 86 }

hmWanMbus5CValue28		OBJECT-TYPE
			SYNTAX	INTEGER
			MAX-ACCESS	read-only
			STATUS	current
			::= { hmWanMbus5C 87 }

hmWanMbus5CVIF29		OBJECT-TYPE
			SYNTAX	INTEGER
			MAX-ACCESS	read-only
			STATUS	current
			::= { hmWanMbus5C 88 }

hmWanMbus5CValue29		OBJECT-TYPE
			SYNTAX	INTEGER
			MAX-ACCESS	read-only
			STATUS	current
			::= { hmWanMbus5C 89 }

hmWanMbus5CVIF2A		OBJECT-TYPE
			SYNTAX	INTEGER
			MAX-ACCESS	read-only
			STATUS	current
			::= { hmWanMbus5C 90 }

hmWanMbus5CValue2A		OBJECT-TYPE
			SYNTAX	INTEGER
			MAX-ACCESS	read-only
			STATUS	current
			::= { hmWanMbus5C 91 }

hmWanMbus5CVIF2B		OBJECT-TYPE
			SYNTAX	INTEGER
			MAX-ACCESS	read-only
			STATUS	current
			::= { hmWanMbus5C 92 }

hmWanMbus5CValue2B		OBJECT-TYPE
			SYNTAX	INTEGER
			MAX-ACCESS	read-only
			STATUS	current
			::= { hmWanMbus5C 93 }

hmWanMbus5CVIF2C		OBJECT-TYPE
			SYNTAX	INTEGER
			MAX-ACCESS	read-only
			STATUS	current
			::= { hmWanMbus5C 94 }

hmWanMbus5CValue2C		OBJECT-TYPE
			SYNTAX	INTEGER
			MAX-ACCESS	read-only
			STATUS	current
			::= { hmWanMbus5C 95 }

hmWanMbus5CVIF2D		OBJECT-TYPE
			SYNTAX	INTEGER
			MAX-ACCESS	read-only
			STATUS	current
			::= { hmWanMbus5C 96 }

hmWanMbus5CValue2D		OBJECT-TYPE
			SYNTAX	INTEGER
			MAX-ACCESS	read-only
			STATUS	current
			::= { hmWanMbus5C 97 }

hmWanMbus5CVIF2E		OBJECT-TYPE
			SYNTAX	INTEGER
			MAX-ACCESS	read-only
			STATUS	current
			::= { hmWanMbus5C 98 }

hmWanMbus5CValue2E		OBJECT-TYPE
			SYNTAX	INTEGER
			MAX-ACCESS	read-only
			STATUS	current
			::= { hmWanMbus5C 99 }

hmWanMbus5CVIF2F		OBJECT-TYPE
			SYNTAX	INTEGER
			MAX-ACCESS	read-only
			STATUS	current
			::= { hmWanMbus5C 100 }

hmWanMbus5CValue2F		OBJECT-TYPE
			SYNTAX	INTEGER
			MAX-ACCESS	read-only
			STATUS	current
			::= { hmWanMbus5C 101 }

hmWanMbus5D			OBJECT IDENTIFIER ::= { hmWanMbus 93 }

hmWanMbus5DIdNumber		OBJECT-TYPE
			SYNTAX	Gauge32
			MAX-ACCESS	read-only
			STATUS	current
			::= { hmWanMbus5D 1 }

hmWanMbus5DManufacturer	OBJECT-TYPE
			SYNTAX	Gauge32
			MAX-ACCESS	read-only
			STATUS	current
			::= { hmWanMbus5D 2 }

hmWanMbus5DVersion		OBJECT-TYPE
			SYNTAX	Gauge32
			MAX-ACCESS	read-only
			STATUS	current
			::= { hmWanMbus5D 3 }

hmWanMbus5DMedium		OBJECT-TYPE
			SYNTAX	Gauge32
			MAX-ACCESS	read-only
			STATUS	current
			::= { hmWanMbus5D 4 }

hmWanMbus5DStatus		OBJECT-TYPE
			SYNTAX	Gauge32
			MAX-ACCESS	read-only
			STATUS	current
			::= { hmWanMbus5D 5 }

hmWanMbus5DVIF00		OBJECT-TYPE
			SYNTAX	INTEGER
			MAX-ACCESS	read-only
			STATUS	current
			::= { hmWanMbus5D 6 }

hmWanMbus5DValue00		OBJECT-TYPE
			SYNTAX	INTEGER
			MAX-ACCESS	read-only
			STATUS	current
			::= { hmWanMbus5D 7 }

hmWanMbus5DVIF01		OBJECT-TYPE
			SYNTAX	INTEGER
			MAX-ACCESS	read-only
			STATUS	current
			::= { hmWanMbus5D 8 }

hmWanMbus5DValue01		OBJECT-TYPE
			SYNTAX	INTEGER
			MAX-ACCESS	read-only
			STATUS	current
			::= { hmWanMbus5D 9 }

hmWanMbus5DVIF02		OBJECT-TYPE
			SYNTAX	INTEGER
			MAX-ACCESS	read-only
			STATUS	current
			::= { hmWanMbus5D 10 }

hmWanMbus5DValue02		OBJECT-TYPE
			SYNTAX	INTEGER
			MAX-ACCESS	read-only
			STATUS	current
			::= { hmWanMbus5D 11 }

hmWanMbus5DVIF03		OBJECT-TYPE
			SYNTAX	INTEGER
			MAX-ACCESS	read-only
			STATUS	current
			::= { hmWanMbus5D 12 }

hmWanMbus5DValue03		OBJECT-TYPE
			SYNTAX	INTEGER
			MAX-ACCESS	read-only
			STATUS	current
			::= { hmWanMbus5D 13 }

hmWanMbus5DVIF04		OBJECT-TYPE
			SYNTAX	INTEGER
			MAX-ACCESS	read-only
			STATUS	current
			::= { hmWanMbus5D 14 }

hmWanMbus5DValue04		OBJECT-TYPE
			SYNTAX	INTEGER
			MAX-ACCESS	read-only
			STATUS	current
			::= { hmWanMbus5D 15 }

hmWanMbus5DVIF05		OBJECT-TYPE
			SYNTAX	INTEGER
			MAX-ACCESS	read-only
			STATUS	current
			::= { hmWanMbus5D 16 }

hmWanMbus5DValue05		OBJECT-TYPE
			SYNTAX	INTEGER
			MAX-ACCESS	read-only
			STATUS	current
			::= { hmWanMbus5D 17 }

hmWanMbus5DVIF06		OBJECT-TYPE
			SYNTAX	INTEGER
			MAX-ACCESS	read-only
			STATUS	current
			::= { hmWanMbus5D 18 }

hmWanMbus5DValue06		OBJECT-TYPE
			SYNTAX	INTEGER
			MAX-ACCESS	read-only
			STATUS	current
			::= { hmWanMbus5D 19 }

hmWanMbus5DVIF07		OBJECT-TYPE
			SYNTAX	INTEGER
			MAX-ACCESS	read-only
			STATUS	current
			::= { hmWanMbus5D 20 }

hmWanMbus5DValue07		OBJECT-TYPE
			SYNTAX	INTEGER
			MAX-ACCESS	read-only
			STATUS	current
			::= { hmWanMbus5D 21 }

hmWanMbus5DVIF08		OBJECT-TYPE
			SYNTAX	INTEGER
			MAX-ACCESS	read-only
			STATUS	current
			::= { hmWanMbus5D 22 }

hmWanMbus5DValue08		OBJECT-TYPE
			SYNTAX	INTEGER
			MAX-ACCESS	read-only
			STATUS	current
			::= { hmWanMbus5D 23 }

hmWanMbus5DVIF09		OBJECT-TYPE
			SYNTAX	INTEGER
			MAX-ACCESS	read-only
			STATUS	current
			::= { hmWanMbus5D 24 }

hmWanMbus5DValue09		OBJECT-TYPE
			SYNTAX	INTEGER
			MAX-ACCESS	read-only
			STATUS	current
			::= { hmWanMbus5D 25 }

hmWanMbus5DVIF0A		OBJECT-TYPE
			SYNTAX	INTEGER
			MAX-ACCESS	read-only
			STATUS	current
			::= { hmWanMbus5D 26 }

hmWanMbus5DValue0A		OBJECT-TYPE
			SYNTAX	INTEGER
			MAX-ACCESS	read-only
			STATUS	current
			::= { hmWanMbus5D 27 }

hmWanMbus5DVIF0B		OBJECT-TYPE
			SYNTAX	INTEGER
			MAX-ACCESS	read-only
			STATUS	current
			::= { hmWanMbus5D 28 }

hmWanMbus5DValue0B		OBJECT-TYPE
			SYNTAX	INTEGER
			MAX-ACCESS	read-only
			STATUS	current
			::= { hmWanMbus5D 29 }

hmWanMbus5DVIF0C		OBJECT-TYPE
			SYNTAX	INTEGER
			MAX-ACCESS	read-only
			STATUS	current
			::= { hmWanMbus5D 30 }

hmWanMbus5DValue0C		OBJECT-TYPE
			SYNTAX	INTEGER
			MAX-ACCESS	read-only
			STATUS	current
			::= { hmWanMbus5D 31 }

hmWanMbus5DVIF0D		OBJECT-TYPE
			SYNTAX	INTEGER
			MAX-ACCESS	read-only
			STATUS	current
			::= { hmWanMbus5D 32 }

hmWanMbus5DValue0D		OBJECT-TYPE
			SYNTAX	INTEGER
			MAX-ACCESS	read-only
			STATUS	current
			::= { hmWanMbus5D 33 }

hmWanMbus5DVIF0E		OBJECT-TYPE
			SYNTAX	INTEGER
			MAX-ACCESS	read-only
			STATUS	current
			::= { hmWanMbus5D 34 }

hmWanMbus5DValue0E		OBJECT-TYPE
			SYNTAX	INTEGER
			MAX-ACCESS	read-only
			STATUS	current
			::= { hmWanMbus5D 35 }

hmWanMbus5DVIF0F		OBJECT-TYPE
			SYNTAX	INTEGER
			MAX-ACCESS	read-only
			STATUS	current
			::= { hmWanMbus5D 36 }

hmWanMbus5DValue0F		OBJECT-TYPE
			SYNTAX	INTEGER
			MAX-ACCESS	read-only
			STATUS	current
			::= { hmWanMbus5D 37 }

hmWanMbus5DVIF10		OBJECT-TYPE
			SYNTAX	INTEGER
			MAX-ACCESS	read-only
			STATUS	current
			::= { hmWanMbus5D 38 }

hmWanMbus5DValue10		OBJECT-TYPE
			SYNTAX	INTEGER
			MAX-ACCESS	read-only
			STATUS	current
			::= { hmWanMbus5D 39 }

hmWanMbus5DVIF11		OBJECT-TYPE
			SYNTAX	INTEGER
			MAX-ACCESS	read-only
			STATUS	current
			::= { hmWanMbus5D 40 }

hmWanMbus5DValue11		OBJECT-TYPE
			SYNTAX	INTEGER
			MAX-ACCESS	read-only
			STATUS	current
			::= { hmWanMbus5D 41 }

hmWanMbus5DVIF12		OBJECT-TYPE
			SYNTAX	INTEGER
			MAX-ACCESS	read-only
			STATUS	current
			::= { hmWanMbus5D 42 }

hmWanMbus5DValue12		OBJECT-TYPE
			SYNTAX	INTEGER
			MAX-ACCESS	read-only
			STATUS	current
			::= { hmWanMbus5D 43 }

hmWanMbus5DVIF13		OBJECT-TYPE
			SYNTAX	INTEGER
			MAX-ACCESS	read-only
			STATUS	current
			::= { hmWanMbus5D 44 }

hmWanMbus5DValue13		OBJECT-TYPE
			SYNTAX	INTEGER
			MAX-ACCESS	read-only
			STATUS	current
			::= { hmWanMbus5D 45 }

hmWanMbus5DVIF14		OBJECT-TYPE
			SYNTAX	INTEGER
			MAX-ACCESS	read-only
			STATUS	current
			::= { hmWanMbus5D 46 }

hmWanMbus5DValue14		OBJECT-TYPE
			SYNTAX	INTEGER
			MAX-ACCESS	read-only
			STATUS	current
			::= { hmWanMbus5D 47 }

hmWanMbus5DVIF15		OBJECT-TYPE
			SYNTAX	INTEGER
			MAX-ACCESS	read-only
			STATUS	current
			::= { hmWanMbus5D 48 }

hmWanMbus5DValue15		OBJECT-TYPE
			SYNTAX	INTEGER
			MAX-ACCESS	read-only
			STATUS	current
			::= { hmWanMbus5D 49 }

hmWanMbus5DVIF16		OBJECT-TYPE
			SYNTAX	INTEGER
			MAX-ACCESS	read-only
			STATUS	current
			::= { hmWanMbus5D 50 }

hmWanMbus5DValue16		OBJECT-TYPE
			SYNTAX	INTEGER
			MAX-ACCESS	read-only
			STATUS	current
			::= { hmWanMbus5D 51 }

hmWanMbus5DVIF17		OBJECT-TYPE
			SYNTAX	INTEGER
			MAX-ACCESS	read-only
			STATUS	current
			::= { hmWanMbus5D 52 }

hmWanMbus5DValue17		OBJECT-TYPE
			SYNTAX	INTEGER
			MAX-ACCESS	read-only
			STATUS	current
			::= { hmWanMbus5D 53 }

hmWanMbus5DVIF18		OBJECT-TYPE
			SYNTAX	INTEGER
			MAX-ACCESS	read-only
			STATUS	current
			::= { hmWanMbus5D 54 }

hmWanMbus5DValue18		OBJECT-TYPE
			SYNTAX	INTEGER
			MAX-ACCESS	read-only
			STATUS	current
			::= { hmWanMbus5D 55 }

hmWanMbus5DVIF19		OBJECT-TYPE
			SYNTAX	INTEGER
			MAX-ACCESS	read-only
			STATUS	current
			::= { hmWanMbus5D 56 }

hmWanMbus5DValue19		OBJECT-TYPE
			SYNTAX	INTEGER
			MAX-ACCESS	read-only
			STATUS	current
			::= { hmWanMbus5D 57 }

hmWanMbus5DVIF1A		OBJECT-TYPE
			SYNTAX	INTEGER
			MAX-ACCESS	read-only
			STATUS	current
			::= { hmWanMbus5D 58 }

hmWanMbus5DValue1A		OBJECT-TYPE
			SYNTAX	INTEGER
			MAX-ACCESS	read-only
			STATUS	current
			::= { hmWanMbus5D 59 }

hmWanMbus5DVIF1B		OBJECT-TYPE
			SYNTAX	INTEGER
			MAX-ACCESS	read-only
			STATUS	current
			::= { hmWanMbus5D 60 }

hmWanMbus5DValue1B		OBJECT-TYPE
			SYNTAX	INTEGER
			MAX-ACCESS	read-only
			STATUS	current
			::= { hmWanMbus5D 61 }

hmWanMbus5DVIF1C		OBJECT-TYPE
			SYNTAX	INTEGER
			MAX-ACCESS	read-only
			STATUS	current
			::= { hmWanMbus5D 62 }

hmWanMbus5DValue1C		OBJECT-TYPE
			SYNTAX	INTEGER
			MAX-ACCESS	read-only
			STATUS	current
			::= { hmWanMbus5D 63 }

hmWanMbus5DVIF1D		OBJECT-TYPE
			SYNTAX	INTEGER
			MAX-ACCESS	read-only
			STATUS	current
			::= { hmWanMbus5D 64 }

hmWanMbus5DValue1D		OBJECT-TYPE
			SYNTAX	INTEGER
			MAX-ACCESS	read-only
			STATUS	current
			::= { hmWanMbus5D 65 }

hmWanMbus5DVIF1E		OBJECT-TYPE
			SYNTAX	INTEGER
			MAX-ACCESS	read-only
			STATUS	current
			::= { hmWanMbus5D 66 }

hmWanMbus5DValue1E		OBJECT-TYPE
			SYNTAX	INTEGER
			MAX-ACCESS	read-only
			STATUS	current
			::= { hmWanMbus5D 67 }

hmWanMbus5DVIF1F		OBJECT-TYPE
			SYNTAX	INTEGER
			MAX-ACCESS	read-only
			STATUS	current
			::= { hmWanMbus5D 68 }

hmWanMbus5DValue1F		OBJECT-TYPE
			SYNTAX	INTEGER
			MAX-ACCESS	read-only
			STATUS	current
			::= { hmWanMbus5D 69 }

hmWanMbus5DVIF20		OBJECT-TYPE
			SYNTAX	INTEGER
			MAX-ACCESS	read-only
			STATUS	current
			::= { hmWanMbus5D 70 }

hmWanMbus5DValue20		OBJECT-TYPE
			SYNTAX	INTEGER
			MAX-ACCESS	read-only
			STATUS	current
			::= { hmWanMbus5D 71 }

hmWanMbus5DVIF21		OBJECT-TYPE
			SYNTAX	INTEGER
			MAX-ACCESS	read-only
			STATUS	current
			::= { hmWanMbus5D 72 }

hmWanMbus5DValue21		OBJECT-TYPE
			SYNTAX	INTEGER
			MAX-ACCESS	read-only
			STATUS	current
			::= { hmWanMbus5D 73 }

hmWanMbus5DVIF22		OBJECT-TYPE
			SYNTAX	INTEGER
			MAX-ACCESS	read-only
			STATUS	current
			::= { hmWanMbus5D 74 }

hmWanMbus5DValue22		OBJECT-TYPE
			SYNTAX	INTEGER
			MAX-ACCESS	read-only
			STATUS	current
			::= { hmWanMbus5D 75 }

hmWanMbus5DVIF23		OBJECT-TYPE
			SYNTAX	INTEGER
			MAX-ACCESS	read-only
			STATUS	current
			::= { hmWanMbus5D 76 }

hmWanMbus5DValue23		OBJECT-TYPE
			SYNTAX	INTEGER
			MAX-ACCESS	read-only
			STATUS	current
			::= { hmWanMbus5D 77 }

hmWanMbus5DVIF24		OBJECT-TYPE
			SYNTAX	INTEGER
			MAX-ACCESS	read-only
			STATUS	current
			::= { hmWanMbus5D 78 }

hmWanMbus5DValue24		OBJECT-TYPE
			SYNTAX	INTEGER
			MAX-ACCESS	read-only
			STATUS	current
			::= { hmWanMbus5D 79 }

hmWanMbus5DVIF25		OBJECT-TYPE
			SYNTAX	INTEGER
			MAX-ACCESS	read-only
			STATUS	current
			::= { hmWanMbus5D 80 }

hmWanMbus5DValue25		OBJECT-TYPE
			SYNTAX	INTEGER
			MAX-ACCESS	read-only
			STATUS	current
			::= { hmWanMbus5D 81 }

hmWanMbus5DVIF26		OBJECT-TYPE
			SYNTAX	INTEGER
			MAX-ACCESS	read-only
			STATUS	current
			::= { hmWanMbus5D 82 }

hmWanMbus5DValue26		OBJECT-TYPE
			SYNTAX	INTEGER
			MAX-ACCESS	read-only
			STATUS	current
			::= { hmWanMbus5D 83 }

hmWanMbus5DVIF27		OBJECT-TYPE
			SYNTAX	INTEGER
			MAX-ACCESS	read-only
			STATUS	current
			::= { hmWanMbus5D 84 }

hmWanMbus5DValue27		OBJECT-TYPE
			SYNTAX	INTEGER
			MAX-ACCESS	read-only
			STATUS	current
			::= { hmWanMbus5D 85 }

hmWanMbus5DVIF28		OBJECT-TYPE
			SYNTAX	INTEGER
			MAX-ACCESS	read-only
			STATUS	current
			::= { hmWanMbus5D 86 }

hmWanMbus5DValue28		OBJECT-TYPE
			SYNTAX	INTEGER
			MAX-ACCESS	read-only
			STATUS	current
			::= { hmWanMbus5D 87 }

hmWanMbus5DVIF29		OBJECT-TYPE
			SYNTAX	INTEGER
			MAX-ACCESS	read-only
			STATUS	current
			::= { hmWanMbus5D 88 }

hmWanMbus5DValue29		OBJECT-TYPE
			SYNTAX	INTEGER
			MAX-ACCESS	read-only
			STATUS	current
			::= { hmWanMbus5D 89 }

hmWanMbus5DVIF2A		OBJECT-TYPE
			SYNTAX	INTEGER
			MAX-ACCESS	read-only
			STATUS	current
			::= { hmWanMbus5D 90 }

hmWanMbus5DValue2A		OBJECT-TYPE
			SYNTAX	INTEGER
			MAX-ACCESS	read-only
			STATUS	current
			::= { hmWanMbus5D 91 }

hmWanMbus5DVIF2B		OBJECT-TYPE
			SYNTAX	INTEGER
			MAX-ACCESS	read-only
			STATUS	current
			::= { hmWanMbus5D 92 }

hmWanMbus5DValue2B		OBJECT-TYPE
			SYNTAX	INTEGER
			MAX-ACCESS	read-only
			STATUS	current
			::= { hmWanMbus5D 93 }

hmWanMbus5DVIF2C		OBJECT-TYPE
			SYNTAX	INTEGER
			MAX-ACCESS	read-only
			STATUS	current
			::= { hmWanMbus5D 94 }

hmWanMbus5DValue2C		OBJECT-TYPE
			SYNTAX	INTEGER
			MAX-ACCESS	read-only
			STATUS	current
			::= { hmWanMbus5D 95 }

hmWanMbus5DVIF2D		OBJECT-TYPE
			SYNTAX	INTEGER
			MAX-ACCESS	read-only
			STATUS	current
			::= { hmWanMbus5D 96 }

hmWanMbus5DValue2D		OBJECT-TYPE
			SYNTAX	INTEGER
			MAX-ACCESS	read-only
			STATUS	current
			::= { hmWanMbus5D 97 }

hmWanMbus5DVIF2E		OBJECT-TYPE
			SYNTAX	INTEGER
			MAX-ACCESS	read-only
			STATUS	current
			::= { hmWanMbus5D 98 }

hmWanMbus5DValue2E		OBJECT-TYPE
			SYNTAX	INTEGER
			MAX-ACCESS	read-only
			STATUS	current
			::= { hmWanMbus5D 99 }

hmWanMbus5DVIF2F		OBJECT-TYPE
			SYNTAX	INTEGER
			MAX-ACCESS	read-only
			STATUS	current
			::= { hmWanMbus5D 100 }

hmWanMbus5DValue2F		OBJECT-TYPE
			SYNTAX	INTEGER
			MAX-ACCESS	read-only
			STATUS	current
			::= { hmWanMbus5D 101 }

hmWanMbus5E			OBJECT IDENTIFIER ::= { hmWanMbus 94 }

hmWanMbus5EIdNumber		OBJECT-TYPE
			SYNTAX	Gauge32
			MAX-ACCESS	read-only
			STATUS	current
			::= { hmWanMbus5E 1 }

hmWanMbus5EManufacturer	OBJECT-TYPE
			SYNTAX	Gauge32
			MAX-ACCESS	read-only
			STATUS	current
			::= { hmWanMbus5E 2 }

hmWanMbus5EVersion		OBJECT-TYPE
			SYNTAX	Gauge32
			MAX-ACCESS	read-only
			STATUS	current
			::= { hmWanMbus5E 3 }

hmWanMbus5EMedium		OBJECT-TYPE
			SYNTAX	Gauge32
			MAX-ACCESS	read-only
			STATUS	current
			::= { hmWanMbus5E 4 }

hmWanMbus5EStatus		OBJECT-TYPE
			SYNTAX	Gauge32
			MAX-ACCESS	read-only
			STATUS	current
			::= { hmWanMbus5E 5 }

hmWanMbus5EVIF00		OBJECT-TYPE
			SYNTAX	INTEGER
			MAX-ACCESS	read-only
			STATUS	current
			::= { hmWanMbus5E 6 }

hmWanMbus5EValue00		OBJECT-TYPE
			SYNTAX	INTEGER
			MAX-ACCESS	read-only
			STATUS	current
			::= { hmWanMbus5E 7 }

hmWanMbus5EVIF01		OBJECT-TYPE
			SYNTAX	INTEGER
			MAX-ACCESS	read-only
			STATUS	current
			::= { hmWanMbus5E 8 }

hmWanMbus5EValue01		OBJECT-TYPE
			SYNTAX	INTEGER
			MAX-ACCESS	read-only
			STATUS	current
			::= { hmWanMbus5E 9 }

hmWanMbus5EVIF02		OBJECT-TYPE
			SYNTAX	INTEGER
			MAX-ACCESS	read-only
			STATUS	current
			::= { hmWanMbus5E 10 }

hmWanMbus5EValue02		OBJECT-TYPE
			SYNTAX	INTEGER
			MAX-ACCESS	read-only
			STATUS	current
			::= { hmWanMbus5E 11 }

hmWanMbus5EVIF03		OBJECT-TYPE
			SYNTAX	INTEGER
			MAX-ACCESS	read-only
			STATUS	current
			::= { hmWanMbus5E 12 }

hmWanMbus5EValue03		OBJECT-TYPE
			SYNTAX	INTEGER
			MAX-ACCESS	read-only
			STATUS	current
			::= { hmWanMbus5E 13 }

hmWanMbus5EVIF04		OBJECT-TYPE
			SYNTAX	INTEGER
			MAX-ACCESS	read-only
			STATUS	current
			::= { hmWanMbus5E 14 }

hmWanMbus5EValue04		OBJECT-TYPE
			SYNTAX	INTEGER
			MAX-ACCESS	read-only
			STATUS	current
			::= { hmWanMbus5E 15 }

hmWanMbus5EVIF05		OBJECT-TYPE
			SYNTAX	INTEGER
			MAX-ACCESS	read-only
			STATUS	current
			::= { hmWanMbus5E 16 }

hmWanMbus5EValue05		OBJECT-TYPE
			SYNTAX	INTEGER
			MAX-ACCESS	read-only
			STATUS	current
			::= { hmWanMbus5E 17 }

hmWanMbus5EVIF06		OBJECT-TYPE
			SYNTAX	INTEGER
			MAX-ACCESS	read-only
			STATUS	current
			::= { hmWanMbus5E 18 }

hmWanMbus5EValue06		OBJECT-TYPE
			SYNTAX	INTEGER
			MAX-ACCESS	read-only
			STATUS	current
			::= { hmWanMbus5E 19 }

hmWanMbus5EVIF07		OBJECT-TYPE
			SYNTAX	INTEGER
			MAX-ACCESS	read-only
			STATUS	current
			::= { hmWanMbus5E 20 }

hmWanMbus5EValue07		OBJECT-TYPE
			SYNTAX	INTEGER
			MAX-ACCESS	read-only
			STATUS	current
			::= { hmWanMbus5E 21 }

hmWanMbus5EVIF08		OBJECT-TYPE
			SYNTAX	INTEGER
			MAX-ACCESS	read-only
			STATUS	current
			::= { hmWanMbus5E 22 }

hmWanMbus5EValue08		OBJECT-TYPE
			SYNTAX	INTEGER
			MAX-ACCESS	read-only
			STATUS	current
			::= { hmWanMbus5E 23 }

hmWanMbus5EVIF09		OBJECT-TYPE
			SYNTAX	INTEGER
			MAX-ACCESS	read-only
			STATUS	current
			::= { hmWanMbus5E 24 }

hmWanMbus5EValue09		OBJECT-TYPE
			SYNTAX	INTEGER
			MAX-ACCESS	read-only
			STATUS	current
			::= { hmWanMbus5E 25 }

hmWanMbus5EVIF0A		OBJECT-TYPE
			SYNTAX	INTEGER
			MAX-ACCESS	read-only
			STATUS	current
			::= { hmWanMbus5E 26 }

hmWanMbus5EValue0A		OBJECT-TYPE
			SYNTAX	INTEGER
			MAX-ACCESS	read-only
			STATUS	current
			::= { hmWanMbus5E 27 }

hmWanMbus5EVIF0B		OBJECT-TYPE
			SYNTAX	INTEGER
			MAX-ACCESS	read-only
			STATUS	current
			::= { hmWanMbus5E 28 }

hmWanMbus5EValue0B		OBJECT-TYPE
			SYNTAX	INTEGER
			MAX-ACCESS	read-only
			STATUS	current
			::= { hmWanMbus5E 29 }

hmWanMbus5EVIF0C		OBJECT-TYPE
			SYNTAX	INTEGER
			MAX-ACCESS	read-only
			STATUS	current
			::= { hmWanMbus5E 30 }

hmWanMbus5EValue0C		OBJECT-TYPE
			SYNTAX	INTEGER
			MAX-ACCESS	read-only
			STATUS	current
			::= { hmWanMbus5E 31 }

hmWanMbus5EVIF0D		OBJECT-TYPE
			SYNTAX	INTEGER
			MAX-ACCESS	read-only
			STATUS	current
			::= { hmWanMbus5E 32 }

hmWanMbus5EValue0D		OBJECT-TYPE
			SYNTAX	INTEGER
			MAX-ACCESS	read-only
			STATUS	current
			::= { hmWanMbus5E 33 }

hmWanMbus5EVIF0E		OBJECT-TYPE
			SYNTAX	INTEGER
			MAX-ACCESS	read-only
			STATUS	current
			::= { hmWanMbus5E 34 }

hmWanMbus5EValue0E		OBJECT-TYPE
			SYNTAX	INTEGER
			MAX-ACCESS	read-only
			STATUS	current
			::= { hmWanMbus5E 35 }

hmWanMbus5EVIF0F		OBJECT-TYPE
			SYNTAX	INTEGER
			MAX-ACCESS	read-only
			STATUS	current
			::= { hmWanMbus5E 36 }

hmWanMbus5EValue0F		OBJECT-TYPE
			SYNTAX	INTEGER
			MAX-ACCESS	read-only
			STATUS	current
			::= { hmWanMbus5E 37 }

hmWanMbus5EVIF10		OBJECT-TYPE
			SYNTAX	INTEGER
			MAX-ACCESS	read-only
			STATUS	current
			::= { hmWanMbus5E 38 }

hmWanMbus5EValue10		OBJECT-TYPE
			SYNTAX	INTEGER
			MAX-ACCESS	read-only
			STATUS	current
			::= { hmWanMbus5E 39 }

hmWanMbus5EVIF11		OBJECT-TYPE
			SYNTAX	INTEGER
			MAX-ACCESS	read-only
			STATUS	current
			::= { hmWanMbus5E 40 }

hmWanMbus5EValue11		OBJECT-TYPE
			SYNTAX	INTEGER
			MAX-ACCESS	read-only
			STATUS	current
			::= { hmWanMbus5E 41 }

hmWanMbus5EVIF12		OBJECT-TYPE
			SYNTAX	INTEGER
			MAX-ACCESS	read-only
			STATUS	current
			::= { hmWanMbus5E 42 }

hmWanMbus5EValue12		OBJECT-TYPE
			SYNTAX	INTEGER
			MAX-ACCESS	read-only
			STATUS	current
			::= { hmWanMbus5E 43 }

hmWanMbus5EVIF13		OBJECT-TYPE
			SYNTAX	INTEGER
			MAX-ACCESS	read-only
			STATUS	current
			::= { hmWanMbus5E 44 }

hmWanMbus5EValue13		OBJECT-TYPE
			SYNTAX	INTEGER
			MAX-ACCESS	read-only
			STATUS	current
			::= { hmWanMbus5E 45 }

hmWanMbus5EVIF14		OBJECT-TYPE
			SYNTAX	INTEGER
			MAX-ACCESS	read-only
			STATUS	current
			::= { hmWanMbus5E 46 }

hmWanMbus5EValue14		OBJECT-TYPE
			SYNTAX	INTEGER
			MAX-ACCESS	read-only
			STATUS	current
			::= { hmWanMbus5E 47 }

hmWanMbus5EVIF15		OBJECT-TYPE
			SYNTAX	INTEGER
			MAX-ACCESS	read-only
			STATUS	current
			::= { hmWanMbus5E 48 }

hmWanMbus5EValue15		OBJECT-TYPE
			SYNTAX	INTEGER
			MAX-ACCESS	read-only
			STATUS	current
			::= { hmWanMbus5E 49 }

hmWanMbus5EVIF16		OBJECT-TYPE
			SYNTAX	INTEGER
			MAX-ACCESS	read-only
			STATUS	current
			::= { hmWanMbus5E 50 }

hmWanMbus5EValue16		OBJECT-TYPE
			SYNTAX	INTEGER
			MAX-ACCESS	read-only
			STATUS	current
			::= { hmWanMbus5E 51 }

hmWanMbus5EVIF17		OBJECT-TYPE
			SYNTAX	INTEGER
			MAX-ACCESS	read-only
			STATUS	current
			::= { hmWanMbus5E 52 }

hmWanMbus5EValue17		OBJECT-TYPE
			SYNTAX	INTEGER
			MAX-ACCESS	read-only
			STATUS	current
			::= { hmWanMbus5E 53 }

hmWanMbus5EVIF18		OBJECT-TYPE
			SYNTAX	INTEGER
			MAX-ACCESS	read-only
			STATUS	current
			::= { hmWanMbus5E 54 }

hmWanMbus5EValue18		OBJECT-TYPE
			SYNTAX	INTEGER
			MAX-ACCESS	read-only
			STATUS	current
			::= { hmWanMbus5E 55 }

hmWanMbus5EVIF19		OBJECT-TYPE
			SYNTAX	INTEGER
			MAX-ACCESS	read-only
			STATUS	current
			::= { hmWanMbus5E 56 }

hmWanMbus5EValue19		OBJECT-TYPE
			SYNTAX	INTEGER
			MAX-ACCESS	read-only
			STATUS	current
			::= { hmWanMbus5E 57 }

hmWanMbus5EVIF1A		OBJECT-TYPE
			SYNTAX	INTEGER
			MAX-ACCESS	read-only
			STATUS	current
			::= { hmWanMbus5E 58 }

hmWanMbus5EValue1A		OBJECT-TYPE
			SYNTAX	INTEGER
			MAX-ACCESS	read-only
			STATUS	current
			::= { hmWanMbus5E 59 }

hmWanMbus5EVIF1B		OBJECT-TYPE
			SYNTAX	INTEGER
			MAX-ACCESS	read-only
			STATUS	current
			::= { hmWanMbus5E 60 }

hmWanMbus5EValue1B		OBJECT-TYPE
			SYNTAX	INTEGER
			MAX-ACCESS	read-only
			STATUS	current
			::= { hmWanMbus5E 61 }

hmWanMbus5EVIF1C		OBJECT-TYPE
			SYNTAX	INTEGER
			MAX-ACCESS	read-only
			STATUS	current
			::= { hmWanMbus5E 62 }

hmWanMbus5EValue1C		OBJECT-TYPE
			SYNTAX	INTEGER
			MAX-ACCESS	read-only
			STATUS	current
			::= { hmWanMbus5E 63 }

hmWanMbus5EVIF1D		OBJECT-TYPE
			SYNTAX	INTEGER
			MAX-ACCESS	read-only
			STATUS	current
			::= { hmWanMbus5E 64 }

hmWanMbus5EValue1D		OBJECT-TYPE
			SYNTAX	INTEGER
			MAX-ACCESS	read-only
			STATUS	current
			::= { hmWanMbus5E 65 }

hmWanMbus5EVIF1E		OBJECT-TYPE
			SYNTAX	INTEGER
			MAX-ACCESS	read-only
			STATUS	current
			::= { hmWanMbus5E 66 }

hmWanMbus5EValue1E		OBJECT-TYPE
			SYNTAX	INTEGER
			MAX-ACCESS	read-only
			STATUS	current
			::= { hmWanMbus5E 67 }

hmWanMbus5EVIF1F		OBJECT-TYPE
			SYNTAX	INTEGER
			MAX-ACCESS	read-only
			STATUS	current
			::= { hmWanMbus5E 68 }

hmWanMbus5EValue1F		OBJECT-TYPE
			SYNTAX	INTEGER
			MAX-ACCESS	read-only
			STATUS	current
			::= { hmWanMbus5E 69 }

hmWanMbus5EVIF20		OBJECT-TYPE
			SYNTAX	INTEGER
			MAX-ACCESS	read-only
			STATUS	current
			::= { hmWanMbus5E 70 }

hmWanMbus5EValue20		OBJECT-TYPE
			SYNTAX	INTEGER
			MAX-ACCESS	read-only
			STATUS	current
			::= { hmWanMbus5E 71 }

hmWanMbus5EVIF21		OBJECT-TYPE
			SYNTAX	INTEGER
			MAX-ACCESS	read-only
			STATUS	current
			::= { hmWanMbus5E 72 }

hmWanMbus5EValue21		OBJECT-TYPE
			SYNTAX	INTEGER
			MAX-ACCESS	read-only
			STATUS	current
			::= { hmWanMbus5E 73 }

hmWanMbus5EVIF22		OBJECT-TYPE
			SYNTAX	INTEGER
			MAX-ACCESS	read-only
			STATUS	current
			::= { hmWanMbus5E 74 }

hmWanMbus5EValue22		OBJECT-TYPE
			SYNTAX	INTEGER
			MAX-ACCESS	read-only
			STATUS	current
			::= { hmWanMbus5E 75 }

hmWanMbus5EVIF23		OBJECT-TYPE
			SYNTAX	INTEGER
			MAX-ACCESS	read-only
			STATUS	current
			::= { hmWanMbus5E 76 }

hmWanMbus5EValue23		OBJECT-TYPE
			SYNTAX	INTEGER
			MAX-ACCESS	read-only
			STATUS	current
			::= { hmWanMbus5E 77 }

hmWanMbus5EVIF24		OBJECT-TYPE
			SYNTAX	INTEGER
			MAX-ACCESS	read-only
			STATUS	current
			::= { hmWanMbus5E 78 }

hmWanMbus5EValue24		OBJECT-TYPE
			SYNTAX	INTEGER
			MAX-ACCESS	read-only
			STATUS	current
			::= { hmWanMbus5E 79 }

hmWanMbus5EVIF25		OBJECT-TYPE
			SYNTAX	INTEGER
			MAX-ACCESS	read-only
			STATUS	current
			::= { hmWanMbus5E 80 }

hmWanMbus5EValue25		OBJECT-TYPE
			SYNTAX	INTEGER
			MAX-ACCESS	read-only
			STATUS	current
			::= { hmWanMbus5E 81 }

hmWanMbus5EVIF26		OBJECT-TYPE
			SYNTAX	INTEGER
			MAX-ACCESS	read-only
			STATUS	current
			::= { hmWanMbus5E 82 }

hmWanMbus5EValue26		OBJECT-TYPE
			SYNTAX	INTEGER
			MAX-ACCESS	read-only
			STATUS	current
			::= { hmWanMbus5E 83 }

hmWanMbus5EVIF27		OBJECT-TYPE
			SYNTAX	INTEGER
			MAX-ACCESS	read-only
			STATUS	current
			::= { hmWanMbus5E 84 }

hmWanMbus5EValue27		OBJECT-TYPE
			SYNTAX	INTEGER
			MAX-ACCESS	read-only
			STATUS	current
			::= { hmWanMbus5E 85 }

hmWanMbus5EVIF28		OBJECT-TYPE
			SYNTAX	INTEGER
			MAX-ACCESS	read-only
			STATUS	current
			::= { hmWanMbus5E 86 }

hmWanMbus5EValue28		OBJECT-TYPE
			SYNTAX	INTEGER
			MAX-ACCESS	read-only
			STATUS	current
			::= { hmWanMbus5E 87 }

hmWanMbus5EVIF29		OBJECT-TYPE
			SYNTAX	INTEGER
			MAX-ACCESS	read-only
			STATUS	current
			::= { hmWanMbus5E 88 }

hmWanMbus5EValue29		OBJECT-TYPE
			SYNTAX	INTEGER
			MAX-ACCESS	read-only
			STATUS	current
			::= { hmWanMbus5E 89 }

hmWanMbus5EVIF2A		OBJECT-TYPE
			SYNTAX	INTEGER
			MAX-ACCESS	read-only
			STATUS	current
			::= { hmWanMbus5E 90 }

hmWanMbus5EValue2A		OBJECT-TYPE
			SYNTAX	INTEGER
			MAX-ACCESS	read-only
			STATUS	current
			::= { hmWanMbus5E 91 }

hmWanMbus5EVIF2B		OBJECT-TYPE
			SYNTAX	INTEGER
			MAX-ACCESS	read-only
			STATUS	current
			::= { hmWanMbus5E 92 }

hmWanMbus5EValue2B		OBJECT-TYPE
			SYNTAX	INTEGER
			MAX-ACCESS	read-only
			STATUS	current
			::= { hmWanMbus5E 93 }

hmWanMbus5EVIF2C		OBJECT-TYPE
			SYNTAX	INTEGER
			MAX-ACCESS	read-only
			STATUS	current
			::= { hmWanMbus5E 94 }

hmWanMbus5EValue2C		OBJECT-TYPE
			SYNTAX	INTEGER
			MAX-ACCESS	read-only
			STATUS	current
			::= { hmWanMbus5E 95 }

hmWanMbus5EVIF2D		OBJECT-TYPE
			SYNTAX	INTEGER
			MAX-ACCESS	read-only
			STATUS	current
			::= { hmWanMbus5E 96 }

hmWanMbus5EValue2D		OBJECT-TYPE
			SYNTAX	INTEGER
			MAX-ACCESS	read-only
			STATUS	current
			::= { hmWanMbus5E 97 }

hmWanMbus5EVIF2E		OBJECT-TYPE
			SYNTAX	INTEGER
			MAX-ACCESS	read-only
			STATUS	current
			::= { hmWanMbus5E 98 }

hmWanMbus5EValue2E		OBJECT-TYPE
			SYNTAX	INTEGER
			MAX-ACCESS	read-only
			STATUS	current
			::= { hmWanMbus5E 99 }

hmWanMbus5EVIF2F		OBJECT-TYPE
			SYNTAX	INTEGER
			MAX-ACCESS	read-only
			STATUS	current
			::= { hmWanMbus5E 100 }

hmWanMbus5EValue2F		OBJECT-TYPE
			SYNTAX	INTEGER
			MAX-ACCESS	read-only
			STATUS	current
			::= { hmWanMbus5E 101 }

hmWanMbus5F			OBJECT IDENTIFIER ::= { hmWanMbus 95 }

hmWanMbus5FIdNumber		OBJECT-TYPE
			SYNTAX	Gauge32
			MAX-ACCESS	read-only
			STATUS	current
			::= { hmWanMbus5F 1 }

hmWanMbus5FManufacturer	OBJECT-TYPE
			SYNTAX	Gauge32
			MAX-ACCESS	read-only
			STATUS	current
			::= { hmWanMbus5F 2 }

hmWanMbus5FVersion		OBJECT-TYPE
			SYNTAX	Gauge32
			MAX-ACCESS	read-only
			STATUS	current
			::= { hmWanMbus5F 3 }

hmWanMbus5FMedium		OBJECT-TYPE
			SYNTAX	Gauge32
			MAX-ACCESS	read-only
			STATUS	current
			::= { hmWanMbus5F 4 }

hmWanMbus5FStatus		OBJECT-TYPE
			SYNTAX	Gauge32
			MAX-ACCESS	read-only
			STATUS	current
			::= { hmWanMbus5F 5 }

hmWanMbus5FVIF00		OBJECT-TYPE
			SYNTAX	INTEGER
			MAX-ACCESS	read-only
			STATUS	current
			::= { hmWanMbus5F 6 }

hmWanMbus5FValue00		OBJECT-TYPE
			SYNTAX	INTEGER
			MAX-ACCESS	read-only
			STATUS	current
			::= { hmWanMbus5F 7 }

hmWanMbus5FVIF01		OBJECT-TYPE
			SYNTAX	INTEGER
			MAX-ACCESS	read-only
			STATUS	current
			::= { hmWanMbus5F 8 }

hmWanMbus5FValue01		OBJECT-TYPE
			SYNTAX	INTEGER
			MAX-ACCESS	read-only
			STATUS	current
			::= { hmWanMbus5F 9 }

hmWanMbus5FVIF02		OBJECT-TYPE
			SYNTAX	INTEGER
			MAX-ACCESS	read-only
			STATUS	current
			::= { hmWanMbus5F 10 }

hmWanMbus5FValue02		OBJECT-TYPE
			SYNTAX	INTEGER
			MAX-ACCESS	read-only
			STATUS	current
			::= { hmWanMbus5F 11 }

hmWanMbus5FVIF03		OBJECT-TYPE
			SYNTAX	INTEGER
			MAX-ACCESS	read-only
			STATUS	current
			::= { hmWanMbus5F 12 }

hmWanMbus5FValue03		OBJECT-TYPE
			SYNTAX	INTEGER
			MAX-ACCESS	read-only
			STATUS	current
			::= { hmWanMbus5F 13 }

hmWanMbus5FVIF04		OBJECT-TYPE
			SYNTAX	INTEGER
			MAX-ACCESS	read-only
			STATUS	current
			::= { hmWanMbus5F 14 }

hmWanMbus5FValue04		OBJECT-TYPE
			SYNTAX	INTEGER
			MAX-ACCESS	read-only
			STATUS	current
			::= { hmWanMbus5F 15 }

hmWanMbus5FVIF05		OBJECT-TYPE
			SYNTAX	INTEGER
			MAX-ACCESS	read-only
			STATUS	current
			::= { hmWanMbus5F 16 }

hmWanMbus5FValue05		OBJECT-TYPE
			SYNTAX	INTEGER
			MAX-ACCESS	read-only
			STATUS	current
			::= { hmWanMbus5F 17 }

hmWanMbus5FVIF06		OBJECT-TYPE
			SYNTAX	INTEGER
			MAX-ACCESS	read-only
			STATUS	current
			::= { hmWanMbus5F 18 }

hmWanMbus5FValue06		OBJECT-TYPE
			SYNTAX	INTEGER
			MAX-ACCESS	read-only
			STATUS	current
			::= { hmWanMbus5F 19 }

hmWanMbus5FVIF07		OBJECT-TYPE
			SYNTAX	INTEGER
			MAX-ACCESS	read-only
			STATUS	current
			::= { hmWanMbus5F 20 }

hmWanMbus5FValue07		OBJECT-TYPE
			SYNTAX	INTEGER
			MAX-ACCESS	read-only
			STATUS	current
			::= { hmWanMbus5F 21 }

hmWanMbus5FVIF08		OBJECT-TYPE
			SYNTAX	INTEGER
			MAX-ACCESS	read-only
			STATUS	current
			::= { hmWanMbus5F 22 }

hmWanMbus5FValue08		OBJECT-TYPE
			SYNTAX	INTEGER
			MAX-ACCESS	read-only
			STATUS	current
			::= { hmWanMbus5F 23 }

hmWanMbus5FVIF09		OBJECT-TYPE
			SYNTAX	INTEGER
			MAX-ACCESS	read-only
			STATUS	current
			::= { hmWanMbus5F 24 }

hmWanMbus5FValue09		OBJECT-TYPE
			SYNTAX	INTEGER
			MAX-ACCESS	read-only
			STATUS	current
			::= { hmWanMbus5F 25 }

hmWanMbus5FVIF0A		OBJECT-TYPE
			SYNTAX	INTEGER
			MAX-ACCESS	read-only
			STATUS	current
			::= { hmWanMbus5F 26 }

hmWanMbus5FValue0A		OBJECT-TYPE
			SYNTAX	INTEGER
			MAX-ACCESS	read-only
			STATUS	current
			::= { hmWanMbus5F 27 }

hmWanMbus5FVIF0B		OBJECT-TYPE
			SYNTAX	INTEGER
			MAX-ACCESS	read-only
			STATUS	current
			::= { hmWanMbus5F 28 }

hmWanMbus5FValue0B		OBJECT-TYPE
			SYNTAX	INTEGER
			MAX-ACCESS	read-only
			STATUS	current
			::= { hmWanMbus5F 29 }

hmWanMbus5FVIF0C		OBJECT-TYPE
			SYNTAX	INTEGER
			MAX-ACCESS	read-only
			STATUS	current
			::= { hmWanMbus5F 30 }

hmWanMbus5FValue0C		OBJECT-TYPE
			SYNTAX	INTEGER
			MAX-ACCESS	read-only
			STATUS	current
			::= { hmWanMbus5F 31 }

hmWanMbus5FVIF0D		OBJECT-TYPE
			SYNTAX	INTEGER
			MAX-ACCESS	read-only
			STATUS	current
			::= { hmWanMbus5F 32 }

hmWanMbus5FValue0D		OBJECT-TYPE
			SYNTAX	INTEGER
			MAX-ACCESS	read-only
			STATUS	current
			::= { hmWanMbus5F 33 }

hmWanMbus5FVIF0E		OBJECT-TYPE
			SYNTAX	INTEGER
			MAX-ACCESS	read-only
			STATUS	current
			::= { hmWanMbus5F 34 }

hmWanMbus5FValue0E		OBJECT-TYPE
			SYNTAX	INTEGER
			MAX-ACCESS	read-only
			STATUS	current
			::= { hmWanMbus5F 35 }

hmWanMbus5FVIF0F		OBJECT-TYPE
			SYNTAX	INTEGER
			MAX-ACCESS	read-only
			STATUS	current
			::= { hmWanMbus5F 36 }

hmWanMbus5FValue0F		OBJECT-TYPE
			SYNTAX	INTEGER
			MAX-ACCESS	read-only
			STATUS	current
			::= { hmWanMbus5F 37 }

hmWanMbus5FVIF10		OBJECT-TYPE
			SYNTAX	INTEGER
			MAX-ACCESS	read-only
			STATUS	current
			::= { hmWanMbus5F 38 }

hmWanMbus5FValue10		OBJECT-TYPE
			SYNTAX	INTEGER
			MAX-ACCESS	read-only
			STATUS	current
			::= { hmWanMbus5F 39 }

hmWanMbus5FVIF11		OBJECT-TYPE
			SYNTAX	INTEGER
			MAX-ACCESS	read-only
			STATUS	current
			::= { hmWanMbus5F 40 }

hmWanMbus5FValue11		OBJECT-TYPE
			SYNTAX	INTEGER
			MAX-ACCESS	read-only
			STATUS	current
			::= { hmWanMbus5F 41 }

hmWanMbus5FVIF12		OBJECT-TYPE
			SYNTAX	INTEGER
			MAX-ACCESS	read-only
			STATUS	current
			::= { hmWanMbus5F 42 }

hmWanMbus5FValue12		OBJECT-TYPE
			SYNTAX	INTEGER
			MAX-ACCESS	read-only
			STATUS	current
			::= { hmWanMbus5F 43 }

hmWanMbus5FVIF13		OBJECT-TYPE
			SYNTAX	INTEGER
			MAX-ACCESS	read-only
			STATUS	current
			::= { hmWanMbus5F 44 }

hmWanMbus5FValue13		OBJECT-TYPE
			SYNTAX	INTEGER
			MAX-ACCESS	read-only
			STATUS	current
			::= { hmWanMbus5F 45 }

hmWanMbus5FVIF14		OBJECT-TYPE
			SYNTAX	INTEGER
			MAX-ACCESS	read-only
			STATUS	current
			::= { hmWanMbus5F 46 }

hmWanMbus5FValue14		OBJECT-TYPE
			SYNTAX	INTEGER
			MAX-ACCESS	read-only
			STATUS	current
			::= { hmWanMbus5F 47 }

hmWanMbus5FVIF15		OBJECT-TYPE
			SYNTAX	INTEGER
			MAX-ACCESS	read-only
			STATUS	current
			::= { hmWanMbus5F 48 }

hmWanMbus5FValue15		OBJECT-TYPE
			SYNTAX	INTEGER
			MAX-ACCESS	read-only
			STATUS	current
			::= { hmWanMbus5F 49 }

hmWanMbus5FVIF16		OBJECT-TYPE
			SYNTAX	INTEGER
			MAX-ACCESS	read-only
			STATUS	current
			::= { hmWanMbus5F 50 }

hmWanMbus5FValue16		OBJECT-TYPE
			SYNTAX	INTEGER
			MAX-ACCESS	read-only
			STATUS	current
			::= { hmWanMbus5F 51 }

hmWanMbus5FVIF17		OBJECT-TYPE
			SYNTAX	INTEGER
			MAX-ACCESS	read-only
			STATUS	current
			::= { hmWanMbus5F 52 }

hmWanMbus5FValue17		OBJECT-TYPE
			SYNTAX	INTEGER
			MAX-ACCESS	read-only
			STATUS	current
			::= { hmWanMbus5F 53 }

hmWanMbus5FVIF18		OBJECT-TYPE
			SYNTAX	INTEGER
			MAX-ACCESS	read-only
			STATUS	current
			::= { hmWanMbus5F 54 }

hmWanMbus5FValue18		OBJECT-TYPE
			SYNTAX	INTEGER
			MAX-ACCESS	read-only
			STATUS	current
			::= { hmWanMbus5F 55 }

hmWanMbus5FVIF19		OBJECT-TYPE
			SYNTAX	INTEGER
			MAX-ACCESS	read-only
			STATUS	current
			::= { hmWanMbus5F 56 }

hmWanMbus5FValue19		OBJECT-TYPE
			SYNTAX	INTEGER
			MAX-ACCESS	read-only
			STATUS	current
			::= { hmWanMbus5F 57 }

hmWanMbus5FVIF1A		OBJECT-TYPE
			SYNTAX	INTEGER
			MAX-ACCESS	read-only
			STATUS	current
			::= { hmWanMbus5F 58 }

hmWanMbus5FValue1A		OBJECT-TYPE
			SYNTAX	INTEGER
			MAX-ACCESS	read-only
			STATUS	current
			::= { hmWanMbus5F 59 }

hmWanMbus5FVIF1B		OBJECT-TYPE
			SYNTAX	INTEGER
			MAX-ACCESS	read-only
			STATUS	current
			::= { hmWanMbus5F 60 }

hmWanMbus5FValue1B		OBJECT-TYPE
			SYNTAX	INTEGER
			MAX-ACCESS	read-only
			STATUS	current
			::= { hmWanMbus5F 61 }

hmWanMbus5FVIF1C		OBJECT-TYPE
			SYNTAX	INTEGER
			MAX-ACCESS	read-only
			STATUS	current
			::= { hmWanMbus5F 62 }

hmWanMbus5FValue1C		OBJECT-TYPE
			SYNTAX	INTEGER
			MAX-ACCESS	read-only
			STATUS	current
			::= { hmWanMbus5F 63 }

hmWanMbus5FVIF1D		OBJECT-TYPE
			SYNTAX	INTEGER
			MAX-ACCESS	read-only
			STATUS	current
			::= { hmWanMbus5F 64 }

hmWanMbus5FValue1D		OBJECT-TYPE
			SYNTAX	INTEGER
			MAX-ACCESS	read-only
			STATUS	current
			::= { hmWanMbus5F 65 }

hmWanMbus5FVIF1E		OBJECT-TYPE
			SYNTAX	INTEGER
			MAX-ACCESS	read-only
			STATUS	current
			::= { hmWanMbus5F 66 }

hmWanMbus5FValue1E		OBJECT-TYPE
			SYNTAX	INTEGER
			MAX-ACCESS	read-only
			STATUS	current
			::= { hmWanMbus5F 67 }

hmWanMbus5FVIF1F		OBJECT-TYPE
			SYNTAX	INTEGER
			MAX-ACCESS	read-only
			STATUS	current
			::= { hmWanMbus5F 68 }

hmWanMbus5FValue1F		OBJECT-TYPE
			SYNTAX	INTEGER
			MAX-ACCESS	read-only
			STATUS	current
			::= { hmWanMbus5F 69 }

hmWanMbus5FVIF20		OBJECT-TYPE
			SYNTAX	INTEGER
			MAX-ACCESS	read-only
			STATUS	current
			::= { hmWanMbus5F 70 }

hmWanMbus5FValue20		OBJECT-TYPE
			SYNTAX	INTEGER
			MAX-ACCESS	read-only
			STATUS	current
			::= { hmWanMbus5F 71 }

hmWanMbus5FVIF21		OBJECT-TYPE
			SYNTAX	INTEGER
			MAX-ACCESS	read-only
			STATUS	current
			::= { hmWanMbus5F 72 }

hmWanMbus5FValue21		OBJECT-TYPE
			SYNTAX	INTEGER
			MAX-ACCESS	read-only
			STATUS	current
			::= { hmWanMbus5F 73 }

hmWanMbus5FVIF22		OBJECT-TYPE
			SYNTAX	INTEGER
			MAX-ACCESS	read-only
			STATUS	current
			::= { hmWanMbus5F 74 }

hmWanMbus5FValue22		OBJECT-TYPE
			SYNTAX	INTEGER
			MAX-ACCESS	read-only
			STATUS	current
			::= { hmWanMbus5F 75 }

hmWanMbus5FVIF23		OBJECT-TYPE
			SYNTAX	INTEGER
			MAX-ACCESS	read-only
			STATUS	current
			::= { hmWanMbus5F 76 }

hmWanMbus5FValue23		OBJECT-TYPE
			SYNTAX	INTEGER
			MAX-ACCESS	read-only
			STATUS	current
			::= { hmWanMbus5F 77 }

hmWanMbus5FVIF24		OBJECT-TYPE
			SYNTAX	INTEGER
			MAX-ACCESS	read-only
			STATUS	current
			::= { hmWanMbus5F 78 }

hmWanMbus5FValue24		OBJECT-TYPE
			SYNTAX	INTEGER
			MAX-ACCESS	read-only
			STATUS	current
			::= { hmWanMbus5F 79 }

hmWanMbus5FVIF25		OBJECT-TYPE
			SYNTAX	INTEGER
			MAX-ACCESS	read-only
			STATUS	current
			::= { hmWanMbus5F 80 }

hmWanMbus5FValue25		OBJECT-TYPE
			SYNTAX	INTEGER
			MAX-ACCESS	read-only
			STATUS	current
			::= { hmWanMbus5F 81 }

hmWanMbus5FVIF26		OBJECT-TYPE
			SYNTAX	INTEGER
			MAX-ACCESS	read-only
			STATUS	current
			::= { hmWanMbus5F 82 }

hmWanMbus5FValue26		OBJECT-TYPE
			SYNTAX	INTEGER
			MAX-ACCESS	read-only
			STATUS	current
			::= { hmWanMbus5F 83 }

hmWanMbus5FVIF27		OBJECT-TYPE
			SYNTAX	INTEGER
			MAX-ACCESS	read-only
			STATUS	current
			::= { hmWanMbus5F 84 }

hmWanMbus5FValue27		OBJECT-TYPE
			SYNTAX	INTEGER
			MAX-ACCESS	read-only
			STATUS	current
			::= { hmWanMbus5F 85 }

hmWanMbus5FVIF28		OBJECT-TYPE
			SYNTAX	INTEGER
			MAX-ACCESS	read-only
			STATUS	current
			::= { hmWanMbus5F 86 }

hmWanMbus5FValue28		OBJECT-TYPE
			SYNTAX	INTEGER
			MAX-ACCESS	read-only
			STATUS	current
			::= { hmWanMbus5F 87 }

hmWanMbus5FVIF29		OBJECT-TYPE
			SYNTAX	INTEGER
			MAX-ACCESS	read-only
			STATUS	current
			::= { hmWanMbus5F 88 }

hmWanMbus5FValue29		OBJECT-TYPE
			SYNTAX	INTEGER
			MAX-ACCESS	read-only
			STATUS	current
			::= { hmWanMbus5F 89 }

hmWanMbus5FVIF2A		OBJECT-TYPE
			SYNTAX	INTEGER
			MAX-ACCESS	read-only
			STATUS	current
			::= { hmWanMbus5F 90 }

hmWanMbus5FValue2A		OBJECT-TYPE
			SYNTAX	INTEGER
			MAX-ACCESS	read-only
			STATUS	current
			::= { hmWanMbus5F 91 }

hmWanMbus5FVIF2B		OBJECT-TYPE
			SYNTAX	INTEGER
			MAX-ACCESS	read-only
			STATUS	current
			::= { hmWanMbus5F 92 }

hmWanMbus5FValue2B		OBJECT-TYPE
			SYNTAX	INTEGER
			MAX-ACCESS	read-only
			STATUS	current
			::= { hmWanMbus5F 93 }

hmWanMbus5FVIF2C		OBJECT-TYPE
			SYNTAX	INTEGER
			MAX-ACCESS	read-only
			STATUS	current
			::= { hmWanMbus5F 94 }

hmWanMbus5FValue2C		OBJECT-TYPE
			SYNTAX	INTEGER
			MAX-ACCESS	read-only
			STATUS	current
			::= { hmWanMbus5F 95 }

hmWanMbus5FVIF2D		OBJECT-TYPE
			SYNTAX	INTEGER
			MAX-ACCESS	read-only
			STATUS	current
			::= { hmWanMbus5F 96 }

hmWanMbus5FValue2D		OBJECT-TYPE
			SYNTAX	INTEGER
			MAX-ACCESS	read-only
			STATUS	current
			::= { hmWanMbus5F 97 }

hmWanMbus5FVIF2E		OBJECT-TYPE
			SYNTAX	INTEGER
			MAX-ACCESS	read-only
			STATUS	current
			::= { hmWanMbus5F 98 }

hmWanMbus5FValue2E		OBJECT-TYPE
			SYNTAX	INTEGER
			MAX-ACCESS	read-only
			STATUS	current
			::= { hmWanMbus5F 99 }

hmWanMbus5FVIF2F		OBJECT-TYPE
			SYNTAX	INTEGER
			MAX-ACCESS	read-only
			STATUS	current
			::= { hmWanMbus5F 100 }

hmWanMbus5FValue2F		OBJECT-TYPE
			SYNTAX	INTEGER
			MAX-ACCESS	read-only
			STATUS	current
			::= { hmWanMbus5F 101 }

hmWanMbus60			OBJECT IDENTIFIER ::= { hmWanMbus 96 }

hmWanMbus60IdNumber		OBJECT-TYPE
			SYNTAX	Gauge32
			MAX-ACCESS	read-only
			STATUS	current
			::= { hmWanMbus60 1 }

hmWanMbus60Manufacturer	OBJECT-TYPE
			SYNTAX	Gauge32
			MAX-ACCESS	read-only
			STATUS	current
			::= { hmWanMbus60 2 }

hmWanMbus60Version		OBJECT-TYPE
			SYNTAX	Gauge32
			MAX-ACCESS	read-only
			STATUS	current
			::= { hmWanMbus60 3 }

hmWanMbus60Medium		OBJECT-TYPE
			SYNTAX	Gauge32
			MAX-ACCESS	read-only
			STATUS	current
			::= { hmWanMbus60 4 }

hmWanMbus60Status		OBJECT-TYPE
			SYNTAX	Gauge32
			MAX-ACCESS	read-only
			STATUS	current
			::= { hmWanMbus60 5 }

hmWanMbus60VIF00		OBJECT-TYPE
			SYNTAX	INTEGER
			MAX-ACCESS	read-only
			STATUS	current
			::= { hmWanMbus60 6 }

hmWanMbus60Value00		OBJECT-TYPE
			SYNTAX	INTEGER
			MAX-ACCESS	read-only
			STATUS	current
			::= { hmWanMbus60 7 }

hmWanMbus60VIF01		OBJECT-TYPE
			SYNTAX	INTEGER
			MAX-ACCESS	read-only
			STATUS	current
			::= { hmWanMbus60 8 }

hmWanMbus60Value01		OBJECT-TYPE
			SYNTAX	INTEGER
			MAX-ACCESS	read-only
			STATUS	current
			::= { hmWanMbus60 9 }

hmWanMbus60VIF02		OBJECT-TYPE
			SYNTAX	INTEGER
			MAX-ACCESS	read-only
			STATUS	current
			::= { hmWanMbus60 10 }

hmWanMbus60Value02		OBJECT-TYPE
			SYNTAX	INTEGER
			MAX-ACCESS	read-only
			STATUS	current
			::= { hmWanMbus60 11 }

hmWanMbus60VIF03		OBJECT-TYPE
			SYNTAX	INTEGER
			MAX-ACCESS	read-only
			STATUS	current
			::= { hmWanMbus60 12 }

hmWanMbus60Value03		OBJECT-TYPE
			SYNTAX	INTEGER
			MAX-ACCESS	read-only
			STATUS	current
			::= { hmWanMbus60 13 }

hmWanMbus60VIF04		OBJECT-TYPE
			SYNTAX	INTEGER
			MAX-ACCESS	read-only
			STATUS	current
			::= { hmWanMbus60 14 }

hmWanMbus60Value04		OBJECT-TYPE
			SYNTAX	INTEGER
			MAX-ACCESS	read-only
			STATUS	current
			::= { hmWanMbus60 15 }

hmWanMbus60VIF05		OBJECT-TYPE
			SYNTAX	INTEGER
			MAX-ACCESS	read-only
			STATUS	current
			::= { hmWanMbus60 16 }

hmWanMbus60Value05		OBJECT-TYPE
			SYNTAX	INTEGER
			MAX-ACCESS	read-only
			STATUS	current
			::= { hmWanMbus60 17 }

hmWanMbus60VIF06		OBJECT-TYPE
			SYNTAX	INTEGER
			MAX-ACCESS	read-only
			STATUS	current
			::= { hmWanMbus60 18 }

hmWanMbus60Value06		OBJECT-TYPE
			SYNTAX	INTEGER
			MAX-ACCESS	read-only
			STATUS	current
			::= { hmWanMbus60 19 }

hmWanMbus60VIF07		OBJECT-TYPE
			SYNTAX	INTEGER
			MAX-ACCESS	read-only
			STATUS	current
			::= { hmWanMbus60 20 }

hmWanMbus60Value07		OBJECT-TYPE
			SYNTAX	INTEGER
			MAX-ACCESS	read-only
			STATUS	current
			::= { hmWanMbus60 21 }

hmWanMbus60VIF08		OBJECT-TYPE
			SYNTAX	INTEGER
			MAX-ACCESS	read-only
			STATUS	current
			::= { hmWanMbus60 22 }

hmWanMbus60Value08		OBJECT-TYPE
			SYNTAX	INTEGER
			MAX-ACCESS	read-only
			STATUS	current
			::= { hmWanMbus60 23 }

hmWanMbus60VIF09		OBJECT-TYPE
			SYNTAX	INTEGER
			MAX-ACCESS	read-only
			STATUS	current
			::= { hmWanMbus60 24 }

hmWanMbus60Value09		OBJECT-TYPE
			SYNTAX	INTEGER
			MAX-ACCESS	read-only
			STATUS	current
			::= { hmWanMbus60 25 }

hmWanMbus60VIF0A		OBJECT-TYPE
			SYNTAX	INTEGER
			MAX-ACCESS	read-only
			STATUS	current
			::= { hmWanMbus60 26 }

hmWanMbus60Value0A		OBJECT-TYPE
			SYNTAX	INTEGER
			MAX-ACCESS	read-only
			STATUS	current
			::= { hmWanMbus60 27 }

hmWanMbus60VIF0B		OBJECT-TYPE
			SYNTAX	INTEGER
			MAX-ACCESS	read-only
			STATUS	current
			::= { hmWanMbus60 28 }

hmWanMbus60Value0B		OBJECT-TYPE
			SYNTAX	INTEGER
			MAX-ACCESS	read-only
			STATUS	current
			::= { hmWanMbus60 29 }

hmWanMbus60VIF0C		OBJECT-TYPE
			SYNTAX	INTEGER
			MAX-ACCESS	read-only
			STATUS	current
			::= { hmWanMbus60 30 }

hmWanMbus60Value0C		OBJECT-TYPE
			SYNTAX	INTEGER
			MAX-ACCESS	read-only
			STATUS	current
			::= { hmWanMbus60 31 }

hmWanMbus60VIF0D		OBJECT-TYPE
			SYNTAX	INTEGER
			MAX-ACCESS	read-only
			STATUS	current
			::= { hmWanMbus60 32 }

hmWanMbus60Value0D		OBJECT-TYPE
			SYNTAX	INTEGER
			MAX-ACCESS	read-only
			STATUS	current
			::= { hmWanMbus60 33 }

hmWanMbus60VIF0E		OBJECT-TYPE
			SYNTAX	INTEGER
			MAX-ACCESS	read-only
			STATUS	current
			::= { hmWanMbus60 34 }

hmWanMbus60Value0E		OBJECT-TYPE
			SYNTAX	INTEGER
			MAX-ACCESS	read-only
			STATUS	current
			::= { hmWanMbus60 35 }

hmWanMbus60VIF0F		OBJECT-TYPE
			SYNTAX	INTEGER
			MAX-ACCESS	read-only
			STATUS	current
			::= { hmWanMbus60 36 }

hmWanMbus60Value0F		OBJECT-TYPE
			SYNTAX	INTEGER
			MAX-ACCESS	read-only
			STATUS	current
			::= { hmWanMbus60 37 }

hmWanMbus60VIF10		OBJECT-TYPE
			SYNTAX	INTEGER
			MAX-ACCESS	read-only
			STATUS	current
			::= { hmWanMbus60 38 }

hmWanMbus60Value10		OBJECT-TYPE
			SYNTAX	INTEGER
			MAX-ACCESS	read-only
			STATUS	current
			::= { hmWanMbus60 39 }

hmWanMbus60VIF11		OBJECT-TYPE
			SYNTAX	INTEGER
			MAX-ACCESS	read-only
			STATUS	current
			::= { hmWanMbus60 40 }

hmWanMbus60Value11		OBJECT-TYPE
			SYNTAX	INTEGER
			MAX-ACCESS	read-only
			STATUS	current
			::= { hmWanMbus60 41 }

hmWanMbus60VIF12		OBJECT-TYPE
			SYNTAX	INTEGER
			MAX-ACCESS	read-only
			STATUS	current
			::= { hmWanMbus60 42 }

hmWanMbus60Value12		OBJECT-TYPE
			SYNTAX	INTEGER
			MAX-ACCESS	read-only
			STATUS	current
			::= { hmWanMbus60 43 }

hmWanMbus60VIF13		OBJECT-TYPE
			SYNTAX	INTEGER
			MAX-ACCESS	read-only
			STATUS	current
			::= { hmWanMbus60 44 }

hmWanMbus60Value13		OBJECT-TYPE
			SYNTAX	INTEGER
			MAX-ACCESS	read-only
			STATUS	current
			::= { hmWanMbus60 45 }

hmWanMbus60VIF14		OBJECT-TYPE
			SYNTAX	INTEGER
			MAX-ACCESS	read-only
			STATUS	current
			::= { hmWanMbus60 46 }

hmWanMbus60Value14		OBJECT-TYPE
			SYNTAX	INTEGER
			MAX-ACCESS	read-only
			STATUS	current
			::= { hmWanMbus60 47 }

hmWanMbus60VIF15		OBJECT-TYPE
			SYNTAX	INTEGER
			MAX-ACCESS	read-only
			STATUS	current
			::= { hmWanMbus60 48 }

hmWanMbus60Value15		OBJECT-TYPE
			SYNTAX	INTEGER
			MAX-ACCESS	read-only
			STATUS	current
			::= { hmWanMbus60 49 }

hmWanMbus60VIF16		OBJECT-TYPE
			SYNTAX	INTEGER
			MAX-ACCESS	read-only
			STATUS	current
			::= { hmWanMbus60 50 }

hmWanMbus60Value16		OBJECT-TYPE
			SYNTAX	INTEGER
			MAX-ACCESS	read-only
			STATUS	current
			::= { hmWanMbus60 51 }

hmWanMbus60VIF17		OBJECT-TYPE
			SYNTAX	INTEGER
			MAX-ACCESS	read-only
			STATUS	current
			::= { hmWanMbus60 52 }

hmWanMbus60Value17		OBJECT-TYPE
			SYNTAX	INTEGER
			MAX-ACCESS	read-only
			STATUS	current
			::= { hmWanMbus60 53 }

hmWanMbus60VIF18		OBJECT-TYPE
			SYNTAX	INTEGER
			MAX-ACCESS	read-only
			STATUS	current
			::= { hmWanMbus60 54 }

hmWanMbus60Value18		OBJECT-TYPE
			SYNTAX	INTEGER
			MAX-ACCESS	read-only
			STATUS	current
			::= { hmWanMbus60 55 }

hmWanMbus60VIF19		OBJECT-TYPE
			SYNTAX	INTEGER
			MAX-ACCESS	read-only
			STATUS	current
			::= { hmWanMbus60 56 }

hmWanMbus60Value19		OBJECT-TYPE
			SYNTAX	INTEGER
			MAX-ACCESS	read-only
			STATUS	current
			::= { hmWanMbus60 57 }

hmWanMbus60VIF1A		OBJECT-TYPE
			SYNTAX	INTEGER
			MAX-ACCESS	read-only
			STATUS	current
			::= { hmWanMbus60 58 }

hmWanMbus60Value1A		OBJECT-TYPE
			SYNTAX	INTEGER
			MAX-ACCESS	read-only
			STATUS	current
			::= { hmWanMbus60 59 }

hmWanMbus60VIF1B		OBJECT-TYPE
			SYNTAX	INTEGER
			MAX-ACCESS	read-only
			STATUS	current
			::= { hmWanMbus60 60 }

hmWanMbus60Value1B		OBJECT-TYPE
			SYNTAX	INTEGER
			MAX-ACCESS	read-only
			STATUS	current
			::= { hmWanMbus60 61 }

hmWanMbus60VIF1C		OBJECT-TYPE
			SYNTAX	INTEGER
			MAX-ACCESS	read-only
			STATUS	current
			::= { hmWanMbus60 62 }

hmWanMbus60Value1C		OBJECT-TYPE
			SYNTAX	INTEGER
			MAX-ACCESS	read-only
			STATUS	current
			::= { hmWanMbus60 63 }

hmWanMbus60VIF1D		OBJECT-TYPE
			SYNTAX	INTEGER
			MAX-ACCESS	read-only
			STATUS	current
			::= { hmWanMbus60 64 }

hmWanMbus60Value1D		OBJECT-TYPE
			SYNTAX	INTEGER
			MAX-ACCESS	read-only
			STATUS	current
			::= { hmWanMbus60 65 }

hmWanMbus60VIF1E		OBJECT-TYPE
			SYNTAX	INTEGER
			MAX-ACCESS	read-only
			STATUS	current
			::= { hmWanMbus60 66 }

hmWanMbus60Value1E		OBJECT-TYPE
			SYNTAX	INTEGER
			MAX-ACCESS	read-only
			STATUS	current
			::= { hmWanMbus60 67 }

hmWanMbus60VIF1F		OBJECT-TYPE
			SYNTAX	INTEGER
			MAX-ACCESS	read-only
			STATUS	current
			::= { hmWanMbus60 68 }

hmWanMbus60Value1F		OBJECT-TYPE
			SYNTAX	INTEGER
			MAX-ACCESS	read-only
			STATUS	current
			::= { hmWanMbus60 69 }

hmWanMbus60VIF20		OBJECT-TYPE
			SYNTAX	INTEGER
			MAX-ACCESS	read-only
			STATUS	current
			::= { hmWanMbus60 70 }

hmWanMbus60Value20		OBJECT-TYPE
			SYNTAX	INTEGER
			MAX-ACCESS	read-only
			STATUS	current
			::= { hmWanMbus60 71 }

hmWanMbus60VIF21		OBJECT-TYPE
			SYNTAX	INTEGER
			MAX-ACCESS	read-only
			STATUS	current
			::= { hmWanMbus60 72 }

hmWanMbus60Value21		OBJECT-TYPE
			SYNTAX	INTEGER
			MAX-ACCESS	read-only
			STATUS	current
			::= { hmWanMbus60 73 }

hmWanMbus60VIF22		OBJECT-TYPE
			SYNTAX	INTEGER
			MAX-ACCESS	read-only
			STATUS	current
			::= { hmWanMbus60 74 }

hmWanMbus60Value22		OBJECT-TYPE
			SYNTAX	INTEGER
			MAX-ACCESS	read-only
			STATUS	current
			::= { hmWanMbus60 75 }

hmWanMbus60VIF23		OBJECT-TYPE
			SYNTAX	INTEGER
			MAX-ACCESS	read-only
			STATUS	current
			::= { hmWanMbus60 76 }

hmWanMbus60Value23		OBJECT-TYPE
			SYNTAX	INTEGER
			MAX-ACCESS	read-only
			STATUS	current
			::= { hmWanMbus60 77 }

hmWanMbus60VIF24		OBJECT-TYPE
			SYNTAX	INTEGER
			MAX-ACCESS	read-only
			STATUS	current
			::= { hmWanMbus60 78 }

hmWanMbus60Value24		OBJECT-TYPE
			SYNTAX	INTEGER
			MAX-ACCESS	read-only
			STATUS	current
			::= { hmWanMbus60 79 }

hmWanMbus60VIF25		OBJECT-TYPE
			SYNTAX	INTEGER
			MAX-ACCESS	read-only
			STATUS	current
			::= { hmWanMbus60 80 }

hmWanMbus60Value25		OBJECT-TYPE
			SYNTAX	INTEGER
			MAX-ACCESS	read-only
			STATUS	current
			::= { hmWanMbus60 81 }

hmWanMbus60VIF26		OBJECT-TYPE
			SYNTAX	INTEGER
			MAX-ACCESS	read-only
			STATUS	current
			::= { hmWanMbus60 82 }

hmWanMbus60Value26		OBJECT-TYPE
			SYNTAX	INTEGER
			MAX-ACCESS	read-only
			STATUS	current
			::= { hmWanMbus60 83 }

hmWanMbus60VIF27		OBJECT-TYPE
			SYNTAX	INTEGER
			MAX-ACCESS	read-only
			STATUS	current
			::= { hmWanMbus60 84 }

hmWanMbus60Value27		OBJECT-TYPE
			SYNTAX	INTEGER
			MAX-ACCESS	read-only
			STATUS	current
			::= { hmWanMbus60 85 }

hmWanMbus60VIF28		OBJECT-TYPE
			SYNTAX	INTEGER
			MAX-ACCESS	read-only
			STATUS	current
			::= { hmWanMbus60 86 }

hmWanMbus60Value28		OBJECT-TYPE
			SYNTAX	INTEGER
			MAX-ACCESS	read-only
			STATUS	current
			::= { hmWanMbus60 87 }

hmWanMbus60VIF29		OBJECT-TYPE
			SYNTAX	INTEGER
			MAX-ACCESS	read-only
			STATUS	current
			::= { hmWanMbus60 88 }

hmWanMbus60Value29		OBJECT-TYPE
			SYNTAX	INTEGER
			MAX-ACCESS	read-only
			STATUS	current
			::= { hmWanMbus60 89 }

hmWanMbus60VIF2A		OBJECT-TYPE
			SYNTAX	INTEGER
			MAX-ACCESS	read-only
			STATUS	current
			::= { hmWanMbus60 90 }

hmWanMbus60Value2A		OBJECT-TYPE
			SYNTAX	INTEGER
			MAX-ACCESS	read-only
			STATUS	current
			::= { hmWanMbus60 91 }

hmWanMbus60VIF2B		OBJECT-TYPE
			SYNTAX	INTEGER
			MAX-ACCESS	read-only
			STATUS	current
			::= { hmWanMbus60 92 }

hmWanMbus60Value2B		OBJECT-TYPE
			SYNTAX	INTEGER
			MAX-ACCESS	read-only
			STATUS	current
			::= { hmWanMbus60 93 }

hmWanMbus60VIF2C		OBJECT-TYPE
			SYNTAX	INTEGER
			MAX-ACCESS	read-only
			STATUS	current
			::= { hmWanMbus60 94 }

hmWanMbus60Value2C		OBJECT-TYPE
			SYNTAX	INTEGER
			MAX-ACCESS	read-only
			STATUS	current
			::= { hmWanMbus60 95 }

hmWanMbus60VIF2D		OBJECT-TYPE
			SYNTAX	INTEGER
			MAX-ACCESS	read-only
			STATUS	current
			::= { hmWanMbus60 96 }

hmWanMbus60Value2D		OBJECT-TYPE
			SYNTAX	INTEGER
			MAX-ACCESS	read-only
			STATUS	current
			::= { hmWanMbus60 97 }

hmWanMbus60VIF2E		OBJECT-TYPE
			SYNTAX	INTEGER
			MAX-ACCESS	read-only
			STATUS	current
			::= { hmWanMbus60 98 }

hmWanMbus60Value2E		OBJECT-TYPE
			SYNTAX	INTEGER
			MAX-ACCESS	read-only
			STATUS	current
			::= { hmWanMbus60 99 }

hmWanMbus60VIF2F		OBJECT-TYPE
			SYNTAX	INTEGER
			MAX-ACCESS	read-only
			STATUS	current
			::= { hmWanMbus60 100 }

hmWanMbus60Value2F		OBJECT-TYPE
			SYNTAX	INTEGER
			MAX-ACCESS	read-only
			STATUS	current
			::= { hmWanMbus60 101 }

hmWanMbus61			OBJECT IDENTIFIER ::= { hmWanMbus 97 }

hmWanMbus61IdNumber		OBJECT-TYPE
			SYNTAX	Gauge32
			MAX-ACCESS	read-only
			STATUS	current
			::= { hmWanMbus61 1 }

hmWanMbus61Manufacturer	OBJECT-TYPE
			SYNTAX	Gauge32
			MAX-ACCESS	read-only
			STATUS	current
			::= { hmWanMbus61 2 }

hmWanMbus61Version		OBJECT-TYPE
			SYNTAX	Gauge32
			MAX-ACCESS	read-only
			STATUS	current
			::= { hmWanMbus61 3 }

hmWanMbus61Medium		OBJECT-TYPE
			SYNTAX	Gauge32
			MAX-ACCESS	read-only
			STATUS	current
			::= { hmWanMbus61 4 }

hmWanMbus61Status		OBJECT-TYPE
			SYNTAX	Gauge32
			MAX-ACCESS	read-only
			STATUS	current
			::= { hmWanMbus61 5 }

hmWanMbus61VIF00		OBJECT-TYPE
			SYNTAX	INTEGER
			MAX-ACCESS	read-only
			STATUS	current
			::= { hmWanMbus61 6 }

hmWanMbus61Value00		OBJECT-TYPE
			SYNTAX	INTEGER
			MAX-ACCESS	read-only
			STATUS	current
			::= { hmWanMbus61 7 }

hmWanMbus61VIF01		OBJECT-TYPE
			SYNTAX	INTEGER
			MAX-ACCESS	read-only
			STATUS	current
			::= { hmWanMbus61 8 }

hmWanMbus61Value01		OBJECT-TYPE
			SYNTAX	INTEGER
			MAX-ACCESS	read-only
			STATUS	current
			::= { hmWanMbus61 9 }

hmWanMbus61VIF02		OBJECT-TYPE
			SYNTAX	INTEGER
			MAX-ACCESS	read-only
			STATUS	current
			::= { hmWanMbus61 10 }

hmWanMbus61Value02		OBJECT-TYPE
			SYNTAX	INTEGER
			MAX-ACCESS	read-only
			STATUS	current
			::= { hmWanMbus61 11 }

hmWanMbus61VIF03		OBJECT-TYPE
			SYNTAX	INTEGER
			MAX-ACCESS	read-only
			STATUS	current
			::= { hmWanMbus61 12 }

hmWanMbus61Value03		OBJECT-TYPE
			SYNTAX	INTEGER
			MAX-ACCESS	read-only
			STATUS	current
			::= { hmWanMbus61 13 }

hmWanMbus61VIF04		OBJECT-TYPE
			SYNTAX	INTEGER
			MAX-ACCESS	read-only
			STATUS	current
			::= { hmWanMbus61 14 }

hmWanMbus61Value04		OBJECT-TYPE
			SYNTAX	INTEGER
			MAX-ACCESS	read-only
			STATUS	current
			::= { hmWanMbus61 15 }

hmWanMbus61VIF05		OBJECT-TYPE
			SYNTAX	INTEGER
			MAX-ACCESS	read-only
			STATUS	current
			::= { hmWanMbus61 16 }

hmWanMbus61Value05		OBJECT-TYPE
			SYNTAX	INTEGER
			MAX-ACCESS	read-only
			STATUS	current
			::= { hmWanMbus61 17 }

hmWanMbus61VIF06		OBJECT-TYPE
			SYNTAX	INTEGER
			MAX-ACCESS	read-only
			STATUS	current
			::= { hmWanMbus61 18 }

hmWanMbus61Value06		OBJECT-TYPE
			SYNTAX	INTEGER
			MAX-ACCESS	read-only
			STATUS	current
			::= { hmWanMbus61 19 }

hmWanMbus61VIF07		OBJECT-TYPE
			SYNTAX	INTEGER
			MAX-ACCESS	read-only
			STATUS	current
			::= { hmWanMbus61 20 }

hmWanMbus61Value07		OBJECT-TYPE
			SYNTAX	INTEGER
			MAX-ACCESS	read-only
			STATUS	current
			::= { hmWanMbus61 21 }

hmWanMbus61VIF08		OBJECT-TYPE
			SYNTAX	INTEGER
			MAX-ACCESS	read-only
			STATUS	current
			::= { hmWanMbus61 22 }

hmWanMbus61Value08		OBJECT-TYPE
			SYNTAX	INTEGER
			MAX-ACCESS	read-only
			STATUS	current
			::= { hmWanMbus61 23 }

hmWanMbus61VIF09		OBJECT-TYPE
			SYNTAX	INTEGER
			MAX-ACCESS	read-only
			STATUS	current
			::= { hmWanMbus61 24 }

hmWanMbus61Value09		OBJECT-TYPE
			SYNTAX	INTEGER
			MAX-ACCESS	read-only
			STATUS	current
			::= { hmWanMbus61 25 }

hmWanMbus61VIF0A		OBJECT-TYPE
			SYNTAX	INTEGER
			MAX-ACCESS	read-only
			STATUS	current
			::= { hmWanMbus61 26 }

hmWanMbus61Value0A		OBJECT-TYPE
			SYNTAX	INTEGER
			MAX-ACCESS	read-only
			STATUS	current
			::= { hmWanMbus61 27 }

hmWanMbus61VIF0B		OBJECT-TYPE
			SYNTAX	INTEGER
			MAX-ACCESS	read-only
			STATUS	current
			::= { hmWanMbus61 28 }

hmWanMbus61Value0B		OBJECT-TYPE
			SYNTAX	INTEGER
			MAX-ACCESS	read-only
			STATUS	current
			::= { hmWanMbus61 29 }

hmWanMbus61VIF0C		OBJECT-TYPE
			SYNTAX	INTEGER
			MAX-ACCESS	read-only
			STATUS	current
			::= { hmWanMbus61 30 }

hmWanMbus61Value0C		OBJECT-TYPE
			SYNTAX	INTEGER
			MAX-ACCESS	read-only
			STATUS	current
			::= { hmWanMbus61 31 }

hmWanMbus61VIF0D		OBJECT-TYPE
			SYNTAX	INTEGER
			MAX-ACCESS	read-only
			STATUS	current
			::= { hmWanMbus61 32 }

hmWanMbus61Value0D		OBJECT-TYPE
			SYNTAX	INTEGER
			MAX-ACCESS	read-only
			STATUS	current
			::= { hmWanMbus61 33 }

hmWanMbus61VIF0E		OBJECT-TYPE
			SYNTAX	INTEGER
			MAX-ACCESS	read-only
			STATUS	current
			::= { hmWanMbus61 34 }

hmWanMbus61Value0E		OBJECT-TYPE
			SYNTAX	INTEGER
			MAX-ACCESS	read-only
			STATUS	current
			::= { hmWanMbus61 35 }

hmWanMbus61VIF0F		OBJECT-TYPE
			SYNTAX	INTEGER
			MAX-ACCESS	read-only
			STATUS	current
			::= { hmWanMbus61 36 }

hmWanMbus61Value0F		OBJECT-TYPE
			SYNTAX	INTEGER
			MAX-ACCESS	read-only
			STATUS	current
			::= { hmWanMbus61 37 }

hmWanMbus61VIF10		OBJECT-TYPE
			SYNTAX	INTEGER
			MAX-ACCESS	read-only
			STATUS	current
			::= { hmWanMbus61 38 }

hmWanMbus61Value10		OBJECT-TYPE
			SYNTAX	INTEGER
			MAX-ACCESS	read-only
			STATUS	current
			::= { hmWanMbus61 39 }

hmWanMbus61VIF11		OBJECT-TYPE
			SYNTAX	INTEGER
			MAX-ACCESS	read-only
			STATUS	current
			::= { hmWanMbus61 40 }

hmWanMbus61Value11		OBJECT-TYPE
			SYNTAX	INTEGER
			MAX-ACCESS	read-only
			STATUS	current
			::= { hmWanMbus61 41 }

hmWanMbus61VIF12		OBJECT-TYPE
			SYNTAX	INTEGER
			MAX-ACCESS	read-only
			STATUS	current
			::= { hmWanMbus61 42 }

hmWanMbus61Value12		OBJECT-TYPE
			SYNTAX	INTEGER
			MAX-ACCESS	read-only
			STATUS	current
			::= { hmWanMbus61 43 }

hmWanMbus61VIF13		OBJECT-TYPE
			SYNTAX	INTEGER
			MAX-ACCESS	read-only
			STATUS	current
			::= { hmWanMbus61 44 }

hmWanMbus61Value13		OBJECT-TYPE
			SYNTAX	INTEGER
			MAX-ACCESS	read-only
			STATUS	current
			::= { hmWanMbus61 45 }

hmWanMbus61VIF14		OBJECT-TYPE
			SYNTAX	INTEGER
			MAX-ACCESS	read-only
			STATUS	current
			::= { hmWanMbus61 46 }

hmWanMbus61Value14		OBJECT-TYPE
			SYNTAX	INTEGER
			MAX-ACCESS	read-only
			STATUS	current
			::= { hmWanMbus61 47 }

hmWanMbus61VIF15		OBJECT-TYPE
			SYNTAX	INTEGER
			MAX-ACCESS	read-only
			STATUS	current
			::= { hmWanMbus61 48 }

hmWanMbus61Value15		OBJECT-TYPE
			SYNTAX	INTEGER
			MAX-ACCESS	read-only
			STATUS	current
			::= { hmWanMbus61 49 }

hmWanMbus61VIF16		OBJECT-TYPE
			SYNTAX	INTEGER
			MAX-ACCESS	read-only
			STATUS	current
			::= { hmWanMbus61 50 }

hmWanMbus61Value16		OBJECT-TYPE
			SYNTAX	INTEGER
			MAX-ACCESS	read-only
			STATUS	current
			::= { hmWanMbus61 51 }

hmWanMbus61VIF17		OBJECT-TYPE
			SYNTAX	INTEGER
			MAX-ACCESS	read-only
			STATUS	current
			::= { hmWanMbus61 52 }

hmWanMbus61Value17		OBJECT-TYPE
			SYNTAX	INTEGER
			MAX-ACCESS	read-only
			STATUS	current
			::= { hmWanMbus61 53 }

hmWanMbus61VIF18		OBJECT-TYPE
			SYNTAX	INTEGER
			MAX-ACCESS	read-only
			STATUS	current
			::= { hmWanMbus61 54 }

hmWanMbus61Value18		OBJECT-TYPE
			SYNTAX	INTEGER
			MAX-ACCESS	read-only
			STATUS	current
			::= { hmWanMbus61 55 }

hmWanMbus61VIF19		OBJECT-TYPE
			SYNTAX	INTEGER
			MAX-ACCESS	read-only
			STATUS	current
			::= { hmWanMbus61 56 }

hmWanMbus61Value19		OBJECT-TYPE
			SYNTAX	INTEGER
			MAX-ACCESS	read-only
			STATUS	current
			::= { hmWanMbus61 57 }

hmWanMbus61VIF1A		OBJECT-TYPE
			SYNTAX	INTEGER
			MAX-ACCESS	read-only
			STATUS	current
			::= { hmWanMbus61 58 }

hmWanMbus61Value1A		OBJECT-TYPE
			SYNTAX	INTEGER
			MAX-ACCESS	read-only
			STATUS	current
			::= { hmWanMbus61 59 }

hmWanMbus61VIF1B		OBJECT-TYPE
			SYNTAX	INTEGER
			MAX-ACCESS	read-only
			STATUS	current
			::= { hmWanMbus61 60 }

hmWanMbus61Value1B		OBJECT-TYPE
			SYNTAX	INTEGER
			MAX-ACCESS	read-only
			STATUS	current
			::= { hmWanMbus61 61 }

hmWanMbus61VIF1C		OBJECT-TYPE
			SYNTAX	INTEGER
			MAX-ACCESS	read-only
			STATUS	current
			::= { hmWanMbus61 62 }

hmWanMbus61Value1C		OBJECT-TYPE
			SYNTAX	INTEGER
			MAX-ACCESS	read-only
			STATUS	current
			::= { hmWanMbus61 63 }

hmWanMbus61VIF1D		OBJECT-TYPE
			SYNTAX	INTEGER
			MAX-ACCESS	read-only
			STATUS	current
			::= { hmWanMbus61 64 }

hmWanMbus61Value1D		OBJECT-TYPE
			SYNTAX	INTEGER
			MAX-ACCESS	read-only
			STATUS	current
			::= { hmWanMbus61 65 }

hmWanMbus61VIF1E		OBJECT-TYPE
			SYNTAX	INTEGER
			MAX-ACCESS	read-only
			STATUS	current
			::= { hmWanMbus61 66 }

hmWanMbus61Value1E		OBJECT-TYPE
			SYNTAX	INTEGER
			MAX-ACCESS	read-only
			STATUS	current
			::= { hmWanMbus61 67 }

hmWanMbus61VIF1F		OBJECT-TYPE
			SYNTAX	INTEGER
			MAX-ACCESS	read-only
			STATUS	current
			::= { hmWanMbus61 68 }

hmWanMbus61Value1F		OBJECT-TYPE
			SYNTAX	INTEGER
			MAX-ACCESS	read-only
			STATUS	current
			::= { hmWanMbus61 69 }

hmWanMbus61VIF20		OBJECT-TYPE
			SYNTAX	INTEGER
			MAX-ACCESS	read-only
			STATUS	current
			::= { hmWanMbus61 70 }

hmWanMbus61Value20		OBJECT-TYPE
			SYNTAX	INTEGER
			MAX-ACCESS	read-only
			STATUS	current
			::= { hmWanMbus61 71 }

hmWanMbus61VIF21		OBJECT-TYPE
			SYNTAX	INTEGER
			MAX-ACCESS	read-only
			STATUS	current
			::= { hmWanMbus61 72 }

hmWanMbus61Value21		OBJECT-TYPE
			SYNTAX	INTEGER
			MAX-ACCESS	read-only
			STATUS	current
			::= { hmWanMbus61 73 }

hmWanMbus61VIF22		OBJECT-TYPE
			SYNTAX	INTEGER
			MAX-ACCESS	read-only
			STATUS	current
			::= { hmWanMbus61 74 }

hmWanMbus61Value22		OBJECT-TYPE
			SYNTAX	INTEGER
			MAX-ACCESS	read-only
			STATUS	current
			::= { hmWanMbus61 75 }

hmWanMbus61VIF23		OBJECT-TYPE
			SYNTAX	INTEGER
			MAX-ACCESS	read-only
			STATUS	current
			::= { hmWanMbus61 76 }

hmWanMbus61Value23		OBJECT-TYPE
			SYNTAX	INTEGER
			MAX-ACCESS	read-only
			STATUS	current
			::= { hmWanMbus61 77 }

hmWanMbus61VIF24		OBJECT-TYPE
			SYNTAX	INTEGER
			MAX-ACCESS	read-only
			STATUS	current
			::= { hmWanMbus61 78 }

hmWanMbus61Value24		OBJECT-TYPE
			SYNTAX	INTEGER
			MAX-ACCESS	read-only
			STATUS	current
			::= { hmWanMbus61 79 }

hmWanMbus61VIF25		OBJECT-TYPE
			SYNTAX	INTEGER
			MAX-ACCESS	read-only
			STATUS	current
			::= { hmWanMbus61 80 }

hmWanMbus61Value25		OBJECT-TYPE
			SYNTAX	INTEGER
			MAX-ACCESS	read-only
			STATUS	current
			::= { hmWanMbus61 81 }

hmWanMbus61VIF26		OBJECT-TYPE
			SYNTAX	INTEGER
			MAX-ACCESS	read-only
			STATUS	current
			::= { hmWanMbus61 82 }

hmWanMbus61Value26		OBJECT-TYPE
			SYNTAX	INTEGER
			MAX-ACCESS	read-only
			STATUS	current
			::= { hmWanMbus61 83 }

hmWanMbus61VIF27		OBJECT-TYPE
			SYNTAX	INTEGER
			MAX-ACCESS	read-only
			STATUS	current
			::= { hmWanMbus61 84 }

hmWanMbus61Value27		OBJECT-TYPE
			SYNTAX	INTEGER
			MAX-ACCESS	read-only
			STATUS	current
			::= { hmWanMbus61 85 }

hmWanMbus61VIF28		OBJECT-TYPE
			SYNTAX	INTEGER
			MAX-ACCESS	read-only
			STATUS	current
			::= { hmWanMbus61 86 }

hmWanMbus61Value28		OBJECT-TYPE
			SYNTAX	INTEGER
			MAX-ACCESS	read-only
			STATUS	current
			::= { hmWanMbus61 87 }

hmWanMbus61VIF29		OBJECT-TYPE
			SYNTAX	INTEGER
			MAX-ACCESS	read-only
			STATUS	current
			::= { hmWanMbus61 88 }

hmWanMbus61Value29		OBJECT-TYPE
			SYNTAX	INTEGER
			MAX-ACCESS	read-only
			STATUS	current
			::= { hmWanMbus61 89 }

hmWanMbus61VIF2A		OBJECT-TYPE
			SYNTAX	INTEGER
			MAX-ACCESS	read-only
			STATUS	current
			::= { hmWanMbus61 90 }

hmWanMbus61Value2A		OBJECT-TYPE
			SYNTAX	INTEGER
			MAX-ACCESS	read-only
			STATUS	current
			::= { hmWanMbus61 91 }

hmWanMbus61VIF2B		OBJECT-TYPE
			SYNTAX	INTEGER
			MAX-ACCESS	read-only
			STATUS	current
			::= { hmWanMbus61 92 }

hmWanMbus61Value2B		OBJECT-TYPE
			SYNTAX	INTEGER
			MAX-ACCESS	read-only
			STATUS	current
			::= { hmWanMbus61 93 }

hmWanMbus61VIF2C		OBJECT-TYPE
			SYNTAX	INTEGER
			MAX-ACCESS	read-only
			STATUS	current
			::= { hmWanMbus61 94 }

hmWanMbus61Value2C		OBJECT-TYPE
			SYNTAX	INTEGER
			MAX-ACCESS	read-only
			STATUS	current
			::= { hmWanMbus61 95 }

hmWanMbus61VIF2D		OBJECT-TYPE
			SYNTAX	INTEGER
			MAX-ACCESS	read-only
			STATUS	current
			::= { hmWanMbus61 96 }

hmWanMbus61Value2D		OBJECT-TYPE
			SYNTAX	INTEGER
			MAX-ACCESS	read-only
			STATUS	current
			::= { hmWanMbus61 97 }

hmWanMbus61VIF2E		OBJECT-TYPE
			SYNTAX	INTEGER
			MAX-ACCESS	read-only
			STATUS	current
			::= { hmWanMbus61 98 }

hmWanMbus61Value2E		OBJECT-TYPE
			SYNTAX	INTEGER
			MAX-ACCESS	read-only
			STATUS	current
			::= { hmWanMbus61 99 }

hmWanMbus61VIF2F		OBJECT-TYPE
			SYNTAX	INTEGER
			MAX-ACCESS	read-only
			STATUS	current
			::= { hmWanMbus61 100 }

hmWanMbus61Value2F		OBJECT-TYPE
			SYNTAX	INTEGER
			MAX-ACCESS	read-only
			STATUS	current
			::= { hmWanMbus61 101 }

hmWanMbus62			OBJECT IDENTIFIER ::= { hmWanMbus 98 }

hmWanMbus62IdNumber		OBJECT-TYPE
			SYNTAX	Gauge32
			MAX-ACCESS	read-only
			STATUS	current
			::= { hmWanMbus62 1 }

hmWanMbus62Manufacturer	OBJECT-TYPE
			SYNTAX	Gauge32
			MAX-ACCESS	read-only
			STATUS	current
			::= { hmWanMbus62 2 }

hmWanMbus62Version		OBJECT-TYPE
			SYNTAX	Gauge32
			MAX-ACCESS	read-only
			STATUS	current
			::= { hmWanMbus62 3 }

hmWanMbus62Medium		OBJECT-TYPE
			SYNTAX	Gauge32
			MAX-ACCESS	read-only
			STATUS	current
			::= { hmWanMbus62 4 }

hmWanMbus62Status		OBJECT-TYPE
			SYNTAX	Gauge32
			MAX-ACCESS	read-only
			STATUS	current
			::= { hmWanMbus62 5 }

hmWanMbus62VIF00		OBJECT-TYPE
			SYNTAX	INTEGER
			MAX-ACCESS	read-only
			STATUS	current
			::= { hmWanMbus62 6 }

hmWanMbus62Value00		OBJECT-TYPE
			SYNTAX	INTEGER
			MAX-ACCESS	read-only
			STATUS	current
			::= { hmWanMbus62 7 }

hmWanMbus62VIF01		OBJECT-TYPE
			SYNTAX	INTEGER
			MAX-ACCESS	read-only
			STATUS	current
			::= { hmWanMbus62 8 }

hmWanMbus62Value01		OBJECT-TYPE
			SYNTAX	INTEGER
			MAX-ACCESS	read-only
			STATUS	current
			::= { hmWanMbus62 9 }

hmWanMbus62VIF02		OBJECT-TYPE
			SYNTAX	INTEGER
			MAX-ACCESS	read-only
			STATUS	current
			::= { hmWanMbus62 10 }

hmWanMbus62Value02		OBJECT-TYPE
			SYNTAX	INTEGER
			MAX-ACCESS	read-only
			STATUS	current
			::= { hmWanMbus62 11 }

hmWanMbus62VIF03		OBJECT-TYPE
			SYNTAX	INTEGER
			MAX-ACCESS	read-only
			STATUS	current
			::= { hmWanMbus62 12 }

hmWanMbus62Value03		OBJECT-TYPE
			SYNTAX	INTEGER
			MAX-ACCESS	read-only
			STATUS	current
			::= { hmWanMbus62 13 }

hmWanMbus62VIF04		OBJECT-TYPE
			SYNTAX	INTEGER
			MAX-ACCESS	read-only
			STATUS	current
			::= { hmWanMbus62 14 }

hmWanMbus62Value04		OBJECT-TYPE
			SYNTAX	INTEGER
			MAX-ACCESS	read-only
			STATUS	current
			::= { hmWanMbus62 15 }

hmWanMbus62VIF05		OBJECT-TYPE
			SYNTAX	INTEGER
			MAX-ACCESS	read-only
			STATUS	current
			::= { hmWanMbus62 16 }

hmWanMbus62Value05		OBJECT-TYPE
			SYNTAX	INTEGER
			MAX-ACCESS	read-only
			STATUS	current
			::= { hmWanMbus62 17 }

hmWanMbus62VIF06		OBJECT-TYPE
			SYNTAX	INTEGER
			MAX-ACCESS	read-only
			STATUS	current
			::= { hmWanMbus62 18 }

hmWanMbus62Value06		OBJECT-TYPE
			SYNTAX	INTEGER
			MAX-ACCESS	read-only
			STATUS	current
			::= { hmWanMbus62 19 }

hmWanMbus62VIF07		OBJECT-TYPE
			SYNTAX	INTEGER
			MAX-ACCESS	read-only
			STATUS	current
			::= { hmWanMbus62 20 }

hmWanMbus62Value07		OBJECT-TYPE
			SYNTAX	INTEGER
			MAX-ACCESS	read-only
			STATUS	current
			::= { hmWanMbus62 21 }

hmWanMbus62VIF08		OBJECT-TYPE
			SYNTAX	INTEGER
			MAX-ACCESS	read-only
			STATUS	current
			::= { hmWanMbus62 22 }

hmWanMbus62Value08		OBJECT-TYPE
			SYNTAX	INTEGER
			MAX-ACCESS	read-only
			STATUS	current
			::= { hmWanMbus62 23 }

hmWanMbus62VIF09		OBJECT-TYPE
			SYNTAX	INTEGER
			MAX-ACCESS	read-only
			STATUS	current
			::= { hmWanMbus62 24 }

hmWanMbus62Value09		OBJECT-TYPE
			SYNTAX	INTEGER
			MAX-ACCESS	read-only
			STATUS	current
			::= { hmWanMbus62 25 }

hmWanMbus62VIF0A		OBJECT-TYPE
			SYNTAX	INTEGER
			MAX-ACCESS	read-only
			STATUS	current
			::= { hmWanMbus62 26 }

hmWanMbus62Value0A		OBJECT-TYPE
			SYNTAX	INTEGER
			MAX-ACCESS	read-only
			STATUS	current
			::= { hmWanMbus62 27 }

hmWanMbus62VIF0B		OBJECT-TYPE
			SYNTAX	INTEGER
			MAX-ACCESS	read-only
			STATUS	current
			::= { hmWanMbus62 28 }

hmWanMbus62Value0B		OBJECT-TYPE
			SYNTAX	INTEGER
			MAX-ACCESS	read-only
			STATUS	current
			::= { hmWanMbus62 29 }

hmWanMbus62VIF0C		OBJECT-TYPE
			SYNTAX	INTEGER
			MAX-ACCESS	read-only
			STATUS	current
			::= { hmWanMbus62 30 }

hmWanMbus62Value0C		OBJECT-TYPE
			SYNTAX	INTEGER
			MAX-ACCESS	read-only
			STATUS	current
			::= { hmWanMbus62 31 }

hmWanMbus62VIF0D		OBJECT-TYPE
			SYNTAX	INTEGER
			MAX-ACCESS	read-only
			STATUS	current
			::= { hmWanMbus62 32 }

hmWanMbus62Value0D		OBJECT-TYPE
			SYNTAX	INTEGER
			MAX-ACCESS	read-only
			STATUS	current
			::= { hmWanMbus62 33 }

hmWanMbus62VIF0E		OBJECT-TYPE
			SYNTAX	INTEGER
			MAX-ACCESS	read-only
			STATUS	current
			::= { hmWanMbus62 34 }

hmWanMbus62Value0E		OBJECT-TYPE
			SYNTAX	INTEGER
			MAX-ACCESS	read-only
			STATUS	current
			::= { hmWanMbus62 35 }

hmWanMbus62VIF0F		OBJECT-TYPE
			SYNTAX	INTEGER
			MAX-ACCESS	read-only
			STATUS	current
			::= { hmWanMbus62 36 }

hmWanMbus62Value0F		OBJECT-TYPE
			SYNTAX	INTEGER
			MAX-ACCESS	read-only
			STATUS	current
			::= { hmWanMbus62 37 }

hmWanMbus62VIF10		OBJECT-TYPE
			SYNTAX	INTEGER
			MAX-ACCESS	read-only
			STATUS	current
			::= { hmWanMbus62 38 }

hmWanMbus62Value10		OBJECT-TYPE
			SYNTAX	INTEGER
			MAX-ACCESS	read-only
			STATUS	current
			::= { hmWanMbus62 39 }

hmWanMbus62VIF11		OBJECT-TYPE
			SYNTAX	INTEGER
			MAX-ACCESS	read-only
			STATUS	current
			::= { hmWanMbus62 40 }

hmWanMbus62Value11		OBJECT-TYPE
			SYNTAX	INTEGER
			MAX-ACCESS	read-only
			STATUS	current
			::= { hmWanMbus62 41 }

hmWanMbus62VIF12		OBJECT-TYPE
			SYNTAX	INTEGER
			MAX-ACCESS	read-only
			STATUS	current
			::= { hmWanMbus62 42 }

hmWanMbus62Value12		OBJECT-TYPE
			SYNTAX	INTEGER
			MAX-ACCESS	read-only
			STATUS	current
			::= { hmWanMbus62 43 }

hmWanMbus62VIF13		OBJECT-TYPE
			SYNTAX	INTEGER
			MAX-ACCESS	read-only
			STATUS	current
			::= { hmWanMbus62 44 }

hmWanMbus62Value13		OBJECT-TYPE
			SYNTAX	INTEGER
			MAX-ACCESS	read-only
			STATUS	current
			::= { hmWanMbus62 45 }

hmWanMbus62VIF14		OBJECT-TYPE
			SYNTAX	INTEGER
			MAX-ACCESS	read-only
			STATUS	current
			::= { hmWanMbus62 46 }

hmWanMbus62Value14		OBJECT-TYPE
			SYNTAX	INTEGER
			MAX-ACCESS	read-only
			STATUS	current
			::= { hmWanMbus62 47 }

hmWanMbus62VIF15		OBJECT-TYPE
			SYNTAX	INTEGER
			MAX-ACCESS	read-only
			STATUS	current
			::= { hmWanMbus62 48 }

hmWanMbus62Value15		OBJECT-TYPE
			SYNTAX	INTEGER
			MAX-ACCESS	read-only
			STATUS	current
			::= { hmWanMbus62 49 }

hmWanMbus62VIF16		OBJECT-TYPE
			SYNTAX	INTEGER
			MAX-ACCESS	read-only
			STATUS	current
			::= { hmWanMbus62 50 }

hmWanMbus62Value16		OBJECT-TYPE
			SYNTAX	INTEGER
			MAX-ACCESS	read-only
			STATUS	current
			::= { hmWanMbus62 51 }

hmWanMbus62VIF17		OBJECT-TYPE
			SYNTAX	INTEGER
			MAX-ACCESS	read-only
			STATUS	current
			::= { hmWanMbus62 52 }

hmWanMbus62Value17		OBJECT-TYPE
			SYNTAX	INTEGER
			MAX-ACCESS	read-only
			STATUS	current
			::= { hmWanMbus62 53 }

hmWanMbus62VIF18		OBJECT-TYPE
			SYNTAX	INTEGER
			MAX-ACCESS	read-only
			STATUS	current
			::= { hmWanMbus62 54 }

hmWanMbus62Value18		OBJECT-TYPE
			SYNTAX	INTEGER
			MAX-ACCESS	read-only
			STATUS	current
			::= { hmWanMbus62 55 }

hmWanMbus62VIF19		OBJECT-TYPE
			SYNTAX	INTEGER
			MAX-ACCESS	read-only
			STATUS	current
			::= { hmWanMbus62 56 }

hmWanMbus62Value19		OBJECT-TYPE
			SYNTAX	INTEGER
			MAX-ACCESS	read-only
			STATUS	current
			::= { hmWanMbus62 57 }

hmWanMbus62VIF1A		OBJECT-TYPE
			SYNTAX	INTEGER
			MAX-ACCESS	read-only
			STATUS	current
			::= { hmWanMbus62 58 }

hmWanMbus62Value1A		OBJECT-TYPE
			SYNTAX	INTEGER
			MAX-ACCESS	read-only
			STATUS	current
			::= { hmWanMbus62 59 }

hmWanMbus62VIF1B		OBJECT-TYPE
			SYNTAX	INTEGER
			MAX-ACCESS	read-only
			STATUS	current
			::= { hmWanMbus62 60 }

hmWanMbus62Value1B		OBJECT-TYPE
			SYNTAX	INTEGER
			MAX-ACCESS	read-only
			STATUS	current
			::= { hmWanMbus62 61 }

hmWanMbus62VIF1C		OBJECT-TYPE
			SYNTAX	INTEGER
			MAX-ACCESS	read-only
			STATUS	current
			::= { hmWanMbus62 62 }

hmWanMbus62Value1C		OBJECT-TYPE
			SYNTAX	INTEGER
			MAX-ACCESS	read-only
			STATUS	current
			::= { hmWanMbus62 63 }

hmWanMbus62VIF1D		OBJECT-TYPE
			SYNTAX	INTEGER
			MAX-ACCESS	read-only
			STATUS	current
			::= { hmWanMbus62 64 }

hmWanMbus62Value1D		OBJECT-TYPE
			SYNTAX	INTEGER
			MAX-ACCESS	read-only
			STATUS	current
			::= { hmWanMbus62 65 }

hmWanMbus62VIF1E		OBJECT-TYPE
			SYNTAX	INTEGER
			MAX-ACCESS	read-only
			STATUS	current
			::= { hmWanMbus62 66 }

hmWanMbus62Value1E		OBJECT-TYPE
			SYNTAX	INTEGER
			MAX-ACCESS	read-only
			STATUS	current
			::= { hmWanMbus62 67 }

hmWanMbus62VIF1F		OBJECT-TYPE
			SYNTAX	INTEGER
			MAX-ACCESS	read-only
			STATUS	current
			::= { hmWanMbus62 68 }

hmWanMbus62Value1F		OBJECT-TYPE
			SYNTAX	INTEGER
			MAX-ACCESS	read-only
			STATUS	current
			::= { hmWanMbus62 69 }

hmWanMbus62VIF20		OBJECT-TYPE
			SYNTAX	INTEGER
			MAX-ACCESS	read-only
			STATUS	current
			::= { hmWanMbus62 70 }

hmWanMbus62Value20		OBJECT-TYPE
			SYNTAX	INTEGER
			MAX-ACCESS	read-only
			STATUS	current
			::= { hmWanMbus62 71 }

hmWanMbus62VIF21		OBJECT-TYPE
			SYNTAX	INTEGER
			MAX-ACCESS	read-only
			STATUS	current
			::= { hmWanMbus62 72 }

hmWanMbus62Value21		OBJECT-TYPE
			SYNTAX	INTEGER
			MAX-ACCESS	read-only
			STATUS	current
			::= { hmWanMbus62 73 }

hmWanMbus62VIF22		OBJECT-TYPE
			SYNTAX	INTEGER
			MAX-ACCESS	read-only
			STATUS	current
			::= { hmWanMbus62 74 }

hmWanMbus62Value22		OBJECT-TYPE
			SYNTAX	INTEGER
			MAX-ACCESS	read-only
			STATUS	current
			::= { hmWanMbus62 75 }

hmWanMbus62VIF23		OBJECT-TYPE
			SYNTAX	INTEGER
			MAX-ACCESS	read-only
			STATUS	current
			::= { hmWanMbus62 76 }

hmWanMbus62Value23		OBJECT-TYPE
			SYNTAX	INTEGER
			MAX-ACCESS	read-only
			STATUS	current
			::= { hmWanMbus62 77 }

hmWanMbus62VIF24		OBJECT-TYPE
			SYNTAX	INTEGER
			MAX-ACCESS	read-only
			STATUS	current
			::= { hmWanMbus62 78 }

hmWanMbus62Value24		OBJECT-TYPE
			SYNTAX	INTEGER
			MAX-ACCESS	read-only
			STATUS	current
			::= { hmWanMbus62 79 }

hmWanMbus62VIF25		OBJECT-TYPE
			SYNTAX	INTEGER
			MAX-ACCESS	read-only
			STATUS	current
			::= { hmWanMbus62 80 }

hmWanMbus62Value25		OBJECT-TYPE
			SYNTAX	INTEGER
			MAX-ACCESS	read-only
			STATUS	current
			::= { hmWanMbus62 81 }

hmWanMbus62VIF26		OBJECT-TYPE
			SYNTAX	INTEGER
			MAX-ACCESS	read-only
			STATUS	current
			::= { hmWanMbus62 82 }

hmWanMbus62Value26		OBJECT-TYPE
			SYNTAX	INTEGER
			MAX-ACCESS	read-only
			STATUS	current
			::= { hmWanMbus62 83 }

hmWanMbus62VIF27		OBJECT-TYPE
			SYNTAX	INTEGER
			MAX-ACCESS	read-only
			STATUS	current
			::= { hmWanMbus62 84 }

hmWanMbus62Value27		OBJECT-TYPE
			SYNTAX	INTEGER
			MAX-ACCESS	read-only
			STATUS	current
			::= { hmWanMbus62 85 }

hmWanMbus62VIF28		OBJECT-TYPE
			SYNTAX	INTEGER
			MAX-ACCESS	read-only
			STATUS	current
			::= { hmWanMbus62 86 }

hmWanMbus62Value28		OBJECT-TYPE
			SYNTAX	INTEGER
			MAX-ACCESS	read-only
			STATUS	current
			::= { hmWanMbus62 87 }

hmWanMbus62VIF29		OBJECT-TYPE
			SYNTAX	INTEGER
			MAX-ACCESS	read-only
			STATUS	current
			::= { hmWanMbus62 88 }

hmWanMbus62Value29		OBJECT-TYPE
			SYNTAX	INTEGER
			MAX-ACCESS	read-only
			STATUS	current
			::= { hmWanMbus62 89 }

hmWanMbus62VIF2A		OBJECT-TYPE
			SYNTAX	INTEGER
			MAX-ACCESS	read-only
			STATUS	current
			::= { hmWanMbus62 90 }

hmWanMbus62Value2A		OBJECT-TYPE
			SYNTAX	INTEGER
			MAX-ACCESS	read-only
			STATUS	current
			::= { hmWanMbus62 91 }

hmWanMbus62VIF2B		OBJECT-TYPE
			SYNTAX	INTEGER
			MAX-ACCESS	read-only
			STATUS	current
			::= { hmWanMbus62 92 }

hmWanMbus62Value2B		OBJECT-TYPE
			SYNTAX	INTEGER
			MAX-ACCESS	read-only
			STATUS	current
			::= { hmWanMbus62 93 }

hmWanMbus62VIF2C		OBJECT-TYPE
			SYNTAX	INTEGER
			MAX-ACCESS	read-only
			STATUS	current
			::= { hmWanMbus62 94 }

hmWanMbus62Value2C		OBJECT-TYPE
			SYNTAX	INTEGER
			MAX-ACCESS	read-only
			STATUS	current
			::= { hmWanMbus62 95 }

hmWanMbus62VIF2D		OBJECT-TYPE
			SYNTAX	INTEGER
			MAX-ACCESS	read-only
			STATUS	current
			::= { hmWanMbus62 96 }

hmWanMbus62Value2D		OBJECT-TYPE
			SYNTAX	INTEGER
			MAX-ACCESS	read-only
			STATUS	current
			::= { hmWanMbus62 97 }

hmWanMbus62VIF2E		OBJECT-TYPE
			SYNTAX	INTEGER
			MAX-ACCESS	read-only
			STATUS	current
			::= { hmWanMbus62 98 }

hmWanMbus62Value2E		OBJECT-TYPE
			SYNTAX	INTEGER
			MAX-ACCESS	read-only
			STATUS	current
			::= { hmWanMbus62 99 }

hmWanMbus62VIF2F		OBJECT-TYPE
			SYNTAX	INTEGER
			MAX-ACCESS	read-only
			STATUS	current
			::= { hmWanMbus62 100 }

hmWanMbus62Value2F		OBJECT-TYPE
			SYNTAX	INTEGER
			MAX-ACCESS	read-only
			STATUS	current
			::= { hmWanMbus62 101 }

hmWanMbus63			OBJECT IDENTIFIER ::= { hmWanMbus 99 }

hmWanMbus63IdNumber		OBJECT-TYPE
			SYNTAX	Gauge32
			MAX-ACCESS	read-only
			STATUS	current
			::= { hmWanMbus63 1 }

hmWanMbus63Manufacturer	OBJECT-TYPE
			SYNTAX	Gauge32
			MAX-ACCESS	read-only
			STATUS	current
			::= { hmWanMbus63 2 }

hmWanMbus63Version		OBJECT-TYPE
			SYNTAX	Gauge32
			MAX-ACCESS	read-only
			STATUS	current
			::= { hmWanMbus63 3 }

hmWanMbus63Medium		OBJECT-TYPE
			SYNTAX	Gauge32
			MAX-ACCESS	read-only
			STATUS	current
			::= { hmWanMbus63 4 }

hmWanMbus63Status		OBJECT-TYPE
			SYNTAX	Gauge32
			MAX-ACCESS	read-only
			STATUS	current
			::= { hmWanMbus63 5 }

hmWanMbus63VIF00		OBJECT-TYPE
			SYNTAX	INTEGER
			MAX-ACCESS	read-only
			STATUS	current
			::= { hmWanMbus63 6 }

hmWanMbus63Value00		OBJECT-TYPE
			SYNTAX	INTEGER
			MAX-ACCESS	read-only
			STATUS	current
			::= { hmWanMbus63 7 }

hmWanMbus63VIF01		OBJECT-TYPE
			SYNTAX	INTEGER
			MAX-ACCESS	read-only
			STATUS	current
			::= { hmWanMbus63 8 }

hmWanMbus63Value01		OBJECT-TYPE
			SYNTAX	INTEGER
			MAX-ACCESS	read-only
			STATUS	current
			::= { hmWanMbus63 9 }

hmWanMbus63VIF02		OBJECT-TYPE
			SYNTAX	INTEGER
			MAX-ACCESS	read-only
			STATUS	current
			::= { hmWanMbus63 10 }

hmWanMbus63Value02		OBJECT-TYPE
			SYNTAX	INTEGER
			MAX-ACCESS	read-only
			STATUS	current
			::= { hmWanMbus63 11 }

hmWanMbus63VIF03		OBJECT-TYPE
			SYNTAX	INTEGER
			MAX-ACCESS	read-only
			STATUS	current
			::= { hmWanMbus63 12 }

hmWanMbus63Value03		OBJECT-TYPE
			SYNTAX	INTEGER
			MAX-ACCESS	read-only
			STATUS	current
			::= { hmWanMbus63 13 }

hmWanMbus63VIF04		OBJECT-TYPE
			SYNTAX	INTEGER
			MAX-ACCESS	read-only
			STATUS	current
			::= { hmWanMbus63 14 }

hmWanMbus63Value04		OBJECT-TYPE
			SYNTAX	INTEGER
			MAX-ACCESS	read-only
			STATUS	current
			::= { hmWanMbus63 15 }

hmWanMbus63VIF05		OBJECT-TYPE
			SYNTAX	INTEGER
			MAX-ACCESS	read-only
			STATUS	current
			::= { hmWanMbus63 16 }

hmWanMbus63Value05		OBJECT-TYPE
			SYNTAX	INTEGER
			MAX-ACCESS	read-only
			STATUS	current
			::= { hmWanMbus63 17 }

hmWanMbus63VIF06		OBJECT-TYPE
			SYNTAX	INTEGER
			MAX-ACCESS	read-only
			STATUS	current
			::= { hmWanMbus63 18 }

hmWanMbus63Value06		OBJECT-TYPE
			SYNTAX	INTEGER
			MAX-ACCESS	read-only
			STATUS	current
			::= { hmWanMbus63 19 }

hmWanMbus63VIF07		OBJECT-TYPE
			SYNTAX	INTEGER
			MAX-ACCESS	read-only
			STATUS	current
			::= { hmWanMbus63 20 }

hmWanMbus63Value07		OBJECT-TYPE
			SYNTAX	INTEGER
			MAX-ACCESS	read-only
			STATUS	current
			::= { hmWanMbus63 21 }

hmWanMbus63VIF08		OBJECT-TYPE
			SYNTAX	INTEGER
			MAX-ACCESS	read-only
			STATUS	current
			::= { hmWanMbus63 22 }

hmWanMbus63Value08		OBJECT-TYPE
			SYNTAX	INTEGER
			MAX-ACCESS	read-only
			STATUS	current
			::= { hmWanMbus63 23 }

hmWanMbus63VIF09		OBJECT-TYPE
			SYNTAX	INTEGER
			MAX-ACCESS	read-only
			STATUS	current
			::= { hmWanMbus63 24 }

hmWanMbus63Value09		OBJECT-TYPE
			SYNTAX	INTEGER
			MAX-ACCESS	read-only
			STATUS	current
			::= { hmWanMbus63 25 }

hmWanMbus63VIF0A		OBJECT-TYPE
			SYNTAX	INTEGER
			MAX-ACCESS	read-only
			STATUS	current
			::= { hmWanMbus63 26 }

hmWanMbus63Value0A		OBJECT-TYPE
			SYNTAX	INTEGER
			MAX-ACCESS	read-only
			STATUS	current
			::= { hmWanMbus63 27 }

hmWanMbus63VIF0B		OBJECT-TYPE
			SYNTAX	INTEGER
			MAX-ACCESS	read-only
			STATUS	current
			::= { hmWanMbus63 28 }

hmWanMbus63Value0B		OBJECT-TYPE
			SYNTAX	INTEGER
			MAX-ACCESS	read-only
			STATUS	current
			::= { hmWanMbus63 29 }

hmWanMbus63VIF0C		OBJECT-TYPE
			SYNTAX	INTEGER
			MAX-ACCESS	read-only
			STATUS	current
			::= { hmWanMbus63 30 }

hmWanMbus63Value0C		OBJECT-TYPE
			SYNTAX	INTEGER
			MAX-ACCESS	read-only
			STATUS	current
			::= { hmWanMbus63 31 }

hmWanMbus63VIF0D		OBJECT-TYPE
			SYNTAX	INTEGER
			MAX-ACCESS	read-only
			STATUS	current
			::= { hmWanMbus63 32 }

hmWanMbus63Value0D		OBJECT-TYPE
			SYNTAX	INTEGER
			MAX-ACCESS	read-only
			STATUS	current
			::= { hmWanMbus63 33 }

hmWanMbus63VIF0E		OBJECT-TYPE
			SYNTAX	INTEGER
			MAX-ACCESS	read-only
			STATUS	current
			::= { hmWanMbus63 34 }

hmWanMbus63Value0E		OBJECT-TYPE
			SYNTAX	INTEGER
			MAX-ACCESS	read-only
			STATUS	current
			::= { hmWanMbus63 35 }

hmWanMbus63VIF0F		OBJECT-TYPE
			SYNTAX	INTEGER
			MAX-ACCESS	read-only
			STATUS	current
			::= { hmWanMbus63 36 }

hmWanMbus63Value0F		OBJECT-TYPE
			SYNTAX	INTEGER
			MAX-ACCESS	read-only
			STATUS	current
			::= { hmWanMbus63 37 }

hmWanMbus63VIF10		OBJECT-TYPE
			SYNTAX	INTEGER
			MAX-ACCESS	read-only
			STATUS	current
			::= { hmWanMbus63 38 }

hmWanMbus63Value10		OBJECT-TYPE
			SYNTAX	INTEGER
			MAX-ACCESS	read-only
			STATUS	current
			::= { hmWanMbus63 39 }

hmWanMbus63VIF11		OBJECT-TYPE
			SYNTAX	INTEGER
			MAX-ACCESS	read-only
			STATUS	current
			::= { hmWanMbus63 40 }

hmWanMbus63Value11		OBJECT-TYPE
			SYNTAX	INTEGER
			MAX-ACCESS	read-only
			STATUS	current
			::= { hmWanMbus63 41 }

hmWanMbus63VIF12		OBJECT-TYPE
			SYNTAX	INTEGER
			MAX-ACCESS	read-only
			STATUS	current
			::= { hmWanMbus63 42 }

hmWanMbus63Value12		OBJECT-TYPE
			SYNTAX	INTEGER
			MAX-ACCESS	read-only
			STATUS	current
			::= { hmWanMbus63 43 }

hmWanMbus63VIF13		OBJECT-TYPE
			SYNTAX	INTEGER
			MAX-ACCESS	read-only
			STATUS	current
			::= { hmWanMbus63 44 }

hmWanMbus63Value13		OBJECT-TYPE
			SYNTAX	INTEGER
			MAX-ACCESS	read-only
			STATUS	current
			::= { hmWanMbus63 45 }

hmWanMbus63VIF14		OBJECT-TYPE
			SYNTAX	INTEGER
			MAX-ACCESS	read-only
			STATUS	current
			::= { hmWanMbus63 46 }

hmWanMbus63Value14		OBJECT-TYPE
			SYNTAX	INTEGER
			MAX-ACCESS	read-only
			STATUS	current
			::= { hmWanMbus63 47 }

hmWanMbus63VIF15		OBJECT-TYPE
			SYNTAX	INTEGER
			MAX-ACCESS	read-only
			STATUS	current
			::= { hmWanMbus63 48 }

hmWanMbus63Value15		OBJECT-TYPE
			SYNTAX	INTEGER
			MAX-ACCESS	read-only
			STATUS	current
			::= { hmWanMbus63 49 }

hmWanMbus63VIF16		OBJECT-TYPE
			SYNTAX	INTEGER
			MAX-ACCESS	read-only
			STATUS	current
			::= { hmWanMbus63 50 }

hmWanMbus63Value16		OBJECT-TYPE
			SYNTAX	INTEGER
			MAX-ACCESS	read-only
			STATUS	current
			::= { hmWanMbus63 51 }

hmWanMbus63VIF17		OBJECT-TYPE
			SYNTAX	INTEGER
			MAX-ACCESS	read-only
			STATUS	current
			::= { hmWanMbus63 52 }

hmWanMbus63Value17		OBJECT-TYPE
			SYNTAX	INTEGER
			MAX-ACCESS	read-only
			STATUS	current
			::= { hmWanMbus63 53 }

hmWanMbus63VIF18		OBJECT-TYPE
			SYNTAX	INTEGER
			MAX-ACCESS	read-only
			STATUS	current
			::= { hmWanMbus63 54 }

hmWanMbus63Value18		OBJECT-TYPE
			SYNTAX	INTEGER
			MAX-ACCESS	read-only
			STATUS	current
			::= { hmWanMbus63 55 }

hmWanMbus63VIF19		OBJECT-TYPE
			SYNTAX	INTEGER
			MAX-ACCESS	read-only
			STATUS	current
			::= { hmWanMbus63 56 }

hmWanMbus63Value19		OBJECT-TYPE
			SYNTAX	INTEGER
			MAX-ACCESS	read-only
			STATUS	current
			::= { hmWanMbus63 57 }

hmWanMbus63VIF1A		OBJECT-TYPE
			SYNTAX	INTEGER
			MAX-ACCESS	read-only
			STATUS	current
			::= { hmWanMbus63 58 }

hmWanMbus63Value1A		OBJECT-TYPE
			SYNTAX	INTEGER
			MAX-ACCESS	read-only
			STATUS	current
			::= { hmWanMbus63 59 }

hmWanMbus63VIF1B		OBJECT-TYPE
			SYNTAX	INTEGER
			MAX-ACCESS	read-only
			STATUS	current
			::= { hmWanMbus63 60 }

hmWanMbus63Value1B		OBJECT-TYPE
			SYNTAX	INTEGER
			MAX-ACCESS	read-only
			STATUS	current
			::= { hmWanMbus63 61 }

hmWanMbus63VIF1C		OBJECT-TYPE
			SYNTAX	INTEGER
			MAX-ACCESS	read-only
			STATUS	current
			::= { hmWanMbus63 62 }

hmWanMbus63Value1C		OBJECT-TYPE
			SYNTAX	INTEGER
			MAX-ACCESS	read-only
			STATUS	current
			::= { hmWanMbus63 63 }

hmWanMbus63VIF1D		OBJECT-TYPE
			SYNTAX	INTEGER
			MAX-ACCESS	read-only
			STATUS	current
			::= { hmWanMbus63 64 }

hmWanMbus63Value1D		OBJECT-TYPE
			SYNTAX	INTEGER
			MAX-ACCESS	read-only
			STATUS	current
			::= { hmWanMbus63 65 }

hmWanMbus63VIF1E		OBJECT-TYPE
			SYNTAX	INTEGER
			MAX-ACCESS	read-only
			STATUS	current
			::= { hmWanMbus63 66 }

hmWanMbus63Value1E		OBJECT-TYPE
			SYNTAX	INTEGER
			MAX-ACCESS	read-only
			STATUS	current
			::= { hmWanMbus63 67 }

hmWanMbus63VIF1F		OBJECT-TYPE
			SYNTAX	INTEGER
			MAX-ACCESS	read-only
			STATUS	current
			::= { hmWanMbus63 68 }

hmWanMbus63Value1F		OBJECT-TYPE
			SYNTAX	INTEGER
			MAX-ACCESS	read-only
			STATUS	current
			::= { hmWanMbus63 69 }

hmWanMbus63VIF20		OBJECT-TYPE
			SYNTAX	INTEGER
			MAX-ACCESS	read-only
			STATUS	current
			::= { hmWanMbus63 70 }

hmWanMbus63Value20		OBJECT-TYPE
			SYNTAX	INTEGER
			MAX-ACCESS	read-only
			STATUS	current
			::= { hmWanMbus63 71 }

hmWanMbus63VIF21		OBJECT-TYPE
			SYNTAX	INTEGER
			MAX-ACCESS	read-only
			STATUS	current
			::= { hmWanMbus63 72 }

hmWanMbus63Value21		OBJECT-TYPE
			SYNTAX	INTEGER
			MAX-ACCESS	read-only
			STATUS	current
			::= { hmWanMbus63 73 }

hmWanMbus63VIF22		OBJECT-TYPE
			SYNTAX	INTEGER
			MAX-ACCESS	read-only
			STATUS	current
			::= { hmWanMbus63 74 }

hmWanMbus63Value22		OBJECT-TYPE
			SYNTAX	INTEGER
			MAX-ACCESS	read-only
			STATUS	current
			::= { hmWanMbus63 75 }

hmWanMbus63VIF23		OBJECT-TYPE
			SYNTAX	INTEGER
			MAX-ACCESS	read-only
			STATUS	current
			::= { hmWanMbus63 76 }

hmWanMbus63Value23		OBJECT-TYPE
			SYNTAX	INTEGER
			MAX-ACCESS	read-only
			STATUS	current
			::= { hmWanMbus63 77 }

hmWanMbus63VIF24		OBJECT-TYPE
			SYNTAX	INTEGER
			MAX-ACCESS	read-only
			STATUS	current
			::= { hmWanMbus63 78 }

hmWanMbus63Value24		OBJECT-TYPE
			SYNTAX	INTEGER
			MAX-ACCESS	read-only
			STATUS	current
			::= { hmWanMbus63 79 }

hmWanMbus63VIF25		OBJECT-TYPE
			SYNTAX	INTEGER
			MAX-ACCESS	read-only
			STATUS	current
			::= { hmWanMbus63 80 }

hmWanMbus63Value25		OBJECT-TYPE
			SYNTAX	INTEGER
			MAX-ACCESS	read-only
			STATUS	current
			::= { hmWanMbus63 81 }

hmWanMbus63VIF26		OBJECT-TYPE
			SYNTAX	INTEGER
			MAX-ACCESS	read-only
			STATUS	current
			::= { hmWanMbus63 82 }

hmWanMbus63Value26		OBJECT-TYPE
			SYNTAX	INTEGER
			MAX-ACCESS	read-only
			STATUS	current
			::= { hmWanMbus63 83 }

hmWanMbus63VIF27		OBJECT-TYPE
			SYNTAX	INTEGER
			MAX-ACCESS	read-only
			STATUS	current
			::= { hmWanMbus63 84 }

hmWanMbus63Value27		OBJECT-TYPE
			SYNTAX	INTEGER
			MAX-ACCESS	read-only
			STATUS	current
			::= { hmWanMbus63 85 }

hmWanMbus63VIF28		OBJECT-TYPE
			SYNTAX	INTEGER
			MAX-ACCESS	read-only
			STATUS	current
			::= { hmWanMbus63 86 }

hmWanMbus63Value28		OBJECT-TYPE
			SYNTAX	INTEGER
			MAX-ACCESS	read-only
			STATUS	current
			::= { hmWanMbus63 87 }

hmWanMbus63VIF29		OBJECT-TYPE
			SYNTAX	INTEGER
			MAX-ACCESS	read-only
			STATUS	current
			::= { hmWanMbus63 88 }

hmWanMbus63Value29		OBJECT-TYPE
			SYNTAX	INTEGER
			MAX-ACCESS	read-only
			STATUS	current
			::= { hmWanMbus63 89 }

hmWanMbus63VIF2A		OBJECT-TYPE
			SYNTAX	INTEGER
			MAX-ACCESS	read-only
			STATUS	current
			::= { hmWanMbus63 90 }

hmWanMbus63Value2A		OBJECT-TYPE
			SYNTAX	INTEGER
			MAX-ACCESS	read-only
			STATUS	current
			::= { hmWanMbus63 91 }

hmWanMbus63VIF2B		OBJECT-TYPE
			SYNTAX	INTEGER
			MAX-ACCESS	read-only
			STATUS	current
			::= { hmWanMbus63 92 }

hmWanMbus63Value2B		OBJECT-TYPE
			SYNTAX	INTEGER
			MAX-ACCESS	read-only
			STATUS	current
			::= { hmWanMbus63 93 }

hmWanMbus63VIF2C		OBJECT-TYPE
			SYNTAX	INTEGER
			MAX-ACCESS	read-only
			STATUS	current
			::= { hmWanMbus63 94 }

hmWanMbus63Value2C		OBJECT-TYPE
			SYNTAX	INTEGER
			MAX-ACCESS	read-only
			STATUS	current
			::= { hmWanMbus63 95 }

hmWanMbus63VIF2D		OBJECT-TYPE
			SYNTAX	INTEGER
			MAX-ACCESS	read-only
			STATUS	current
			::= { hmWanMbus63 96 }

hmWanMbus63Value2D		OBJECT-TYPE
			SYNTAX	INTEGER
			MAX-ACCESS	read-only
			STATUS	current
			::= { hmWanMbus63 97 }

hmWanMbus63VIF2E		OBJECT-TYPE
			SYNTAX	INTEGER
			MAX-ACCESS	read-only
			STATUS	current
			::= { hmWanMbus63 98 }

hmWanMbus63Value2E		OBJECT-TYPE
			SYNTAX	INTEGER
			MAX-ACCESS	read-only
			STATUS	current
			::= { hmWanMbus63 99 }

hmWanMbus63VIF2F		OBJECT-TYPE
			SYNTAX	INTEGER
			MAX-ACCESS	read-only
			STATUS	current
			::= { hmWanMbus63 100 }

hmWanMbus63Value2F		OBJECT-TYPE
			SYNTAX	INTEGER
			MAX-ACCESS	read-only
			STATUS	current
			::= { hmWanMbus63 101 }

hmWanMbus64			OBJECT IDENTIFIER ::= { hmWanMbus 100 }

hmWanMbus64IdNumber		OBJECT-TYPE
			SYNTAX	Gauge32
			MAX-ACCESS	read-only
			STATUS	current
			::= { hmWanMbus64 1 }

hmWanMbus64Manufacturer	OBJECT-TYPE
			SYNTAX	Gauge32
			MAX-ACCESS	read-only
			STATUS	current
			::= { hmWanMbus64 2 }

hmWanMbus64Version		OBJECT-TYPE
			SYNTAX	Gauge32
			MAX-ACCESS	read-only
			STATUS	current
			::= { hmWanMbus64 3 }

hmWanMbus64Medium		OBJECT-TYPE
			SYNTAX	Gauge32
			MAX-ACCESS	read-only
			STATUS	current
			::= { hmWanMbus64 4 }

hmWanMbus64Status		OBJECT-TYPE
			SYNTAX	Gauge32
			MAX-ACCESS	read-only
			STATUS	current
			::= { hmWanMbus64 5 }

hmWanMbus64VIF00		OBJECT-TYPE
			SYNTAX	INTEGER
			MAX-ACCESS	read-only
			STATUS	current
			::= { hmWanMbus64 6 }

hmWanMbus64Value00		OBJECT-TYPE
			SYNTAX	INTEGER
			MAX-ACCESS	read-only
			STATUS	current
			::= { hmWanMbus64 7 }

hmWanMbus64VIF01		OBJECT-TYPE
			SYNTAX	INTEGER
			MAX-ACCESS	read-only
			STATUS	current
			::= { hmWanMbus64 8 }

hmWanMbus64Value01		OBJECT-TYPE
			SYNTAX	INTEGER
			MAX-ACCESS	read-only
			STATUS	current
			::= { hmWanMbus64 9 }

hmWanMbus64VIF02		OBJECT-TYPE
			SYNTAX	INTEGER
			MAX-ACCESS	read-only
			STATUS	current
			::= { hmWanMbus64 10 }

hmWanMbus64Value02		OBJECT-TYPE
			SYNTAX	INTEGER
			MAX-ACCESS	read-only
			STATUS	current
			::= { hmWanMbus64 11 }

hmWanMbus64VIF03		OBJECT-TYPE
			SYNTAX	INTEGER
			MAX-ACCESS	read-only
			STATUS	current
			::= { hmWanMbus64 12 }

hmWanMbus64Value03		OBJECT-TYPE
			SYNTAX	INTEGER
			MAX-ACCESS	read-only
			STATUS	current
			::= { hmWanMbus64 13 }

hmWanMbus64VIF04		OBJECT-TYPE
			SYNTAX	INTEGER
			MAX-ACCESS	read-only
			STATUS	current
			::= { hmWanMbus64 14 }

hmWanMbus64Value04		OBJECT-TYPE
			SYNTAX	INTEGER
			MAX-ACCESS	read-only
			STATUS	current
			::= { hmWanMbus64 15 }

hmWanMbus64VIF05		OBJECT-TYPE
			SYNTAX	INTEGER
			MAX-ACCESS	read-only
			STATUS	current
			::= { hmWanMbus64 16 }

hmWanMbus64Value05		OBJECT-TYPE
			SYNTAX	INTEGER
			MAX-ACCESS	read-only
			STATUS	current
			::= { hmWanMbus64 17 }

hmWanMbus64VIF06		OBJECT-TYPE
			SYNTAX	INTEGER
			MAX-ACCESS	read-only
			STATUS	current
			::= { hmWanMbus64 18 }

hmWanMbus64Value06		OBJECT-TYPE
			SYNTAX	INTEGER
			MAX-ACCESS	read-only
			STATUS	current
			::= { hmWanMbus64 19 }

hmWanMbus64VIF07		OBJECT-TYPE
			SYNTAX	INTEGER
			MAX-ACCESS	read-only
			STATUS	current
			::= { hmWanMbus64 20 }

hmWanMbus64Value07		OBJECT-TYPE
			SYNTAX	INTEGER
			MAX-ACCESS	read-only
			STATUS	current
			::= { hmWanMbus64 21 }

hmWanMbus64VIF08		OBJECT-TYPE
			SYNTAX	INTEGER
			MAX-ACCESS	read-only
			STATUS	current
			::= { hmWanMbus64 22 }

hmWanMbus64Value08		OBJECT-TYPE
			SYNTAX	INTEGER
			MAX-ACCESS	read-only
			STATUS	current
			::= { hmWanMbus64 23 }

hmWanMbus64VIF09		OBJECT-TYPE
			SYNTAX	INTEGER
			MAX-ACCESS	read-only
			STATUS	current
			::= { hmWanMbus64 24 }

hmWanMbus64Value09		OBJECT-TYPE
			SYNTAX	INTEGER
			MAX-ACCESS	read-only
			STATUS	current
			::= { hmWanMbus64 25 }

hmWanMbus64VIF0A		OBJECT-TYPE
			SYNTAX	INTEGER
			MAX-ACCESS	read-only
			STATUS	current
			::= { hmWanMbus64 26 }

hmWanMbus64Value0A		OBJECT-TYPE
			SYNTAX	INTEGER
			MAX-ACCESS	read-only
			STATUS	current
			::= { hmWanMbus64 27 }

hmWanMbus64VIF0B		OBJECT-TYPE
			SYNTAX	INTEGER
			MAX-ACCESS	read-only
			STATUS	current
			::= { hmWanMbus64 28 }

hmWanMbus64Value0B		OBJECT-TYPE
			SYNTAX	INTEGER
			MAX-ACCESS	read-only
			STATUS	current
			::= { hmWanMbus64 29 }

hmWanMbus64VIF0C		OBJECT-TYPE
			SYNTAX	INTEGER
			MAX-ACCESS	read-only
			STATUS	current
			::= { hmWanMbus64 30 }

hmWanMbus64Value0C		OBJECT-TYPE
			SYNTAX	INTEGER
			MAX-ACCESS	read-only
			STATUS	current
			::= { hmWanMbus64 31 }

hmWanMbus64VIF0D		OBJECT-TYPE
			SYNTAX	INTEGER
			MAX-ACCESS	read-only
			STATUS	current
			::= { hmWanMbus64 32 }

hmWanMbus64Value0D		OBJECT-TYPE
			SYNTAX	INTEGER
			MAX-ACCESS	read-only
			STATUS	current
			::= { hmWanMbus64 33 }

hmWanMbus64VIF0E		OBJECT-TYPE
			SYNTAX	INTEGER
			MAX-ACCESS	read-only
			STATUS	current
			::= { hmWanMbus64 34 }

hmWanMbus64Value0E		OBJECT-TYPE
			SYNTAX	INTEGER
			MAX-ACCESS	read-only
			STATUS	current
			::= { hmWanMbus64 35 }

hmWanMbus64VIF0F		OBJECT-TYPE
			SYNTAX	INTEGER
			MAX-ACCESS	read-only
			STATUS	current
			::= { hmWanMbus64 36 }

hmWanMbus64Value0F		OBJECT-TYPE
			SYNTAX	INTEGER
			MAX-ACCESS	read-only
			STATUS	current
			::= { hmWanMbus64 37 }

hmWanMbus64VIF10		OBJECT-TYPE
			SYNTAX	INTEGER
			MAX-ACCESS	read-only
			STATUS	current
			::= { hmWanMbus64 38 }

hmWanMbus64Value10		OBJECT-TYPE
			SYNTAX	INTEGER
			MAX-ACCESS	read-only
			STATUS	current
			::= { hmWanMbus64 39 }

hmWanMbus64VIF11		OBJECT-TYPE
			SYNTAX	INTEGER
			MAX-ACCESS	read-only
			STATUS	current
			::= { hmWanMbus64 40 }

hmWanMbus64Value11		OBJECT-TYPE
			SYNTAX	INTEGER
			MAX-ACCESS	read-only
			STATUS	current
			::= { hmWanMbus64 41 }

hmWanMbus64VIF12		OBJECT-TYPE
			SYNTAX	INTEGER
			MAX-ACCESS	read-only
			STATUS	current
			::= { hmWanMbus64 42 }

hmWanMbus64Value12		OBJECT-TYPE
			SYNTAX	INTEGER
			MAX-ACCESS	read-only
			STATUS	current
			::= { hmWanMbus64 43 }

hmWanMbus64VIF13		OBJECT-TYPE
			SYNTAX	INTEGER
			MAX-ACCESS	read-only
			STATUS	current
			::= { hmWanMbus64 44 }

hmWanMbus64Value13		OBJECT-TYPE
			SYNTAX	INTEGER
			MAX-ACCESS	read-only
			STATUS	current
			::= { hmWanMbus64 45 }

hmWanMbus64VIF14		OBJECT-TYPE
			SYNTAX	INTEGER
			MAX-ACCESS	read-only
			STATUS	current
			::= { hmWanMbus64 46 }

hmWanMbus64Value14		OBJECT-TYPE
			SYNTAX	INTEGER
			MAX-ACCESS	read-only
			STATUS	current
			::= { hmWanMbus64 47 }

hmWanMbus64VIF15		OBJECT-TYPE
			SYNTAX	INTEGER
			MAX-ACCESS	read-only
			STATUS	current
			::= { hmWanMbus64 48 }

hmWanMbus64Value15		OBJECT-TYPE
			SYNTAX	INTEGER
			MAX-ACCESS	read-only
			STATUS	current
			::= { hmWanMbus64 49 }

hmWanMbus64VIF16		OBJECT-TYPE
			SYNTAX	INTEGER
			MAX-ACCESS	read-only
			STATUS	current
			::= { hmWanMbus64 50 }

hmWanMbus64Value16		OBJECT-TYPE
			SYNTAX	INTEGER
			MAX-ACCESS	read-only
			STATUS	current
			::= { hmWanMbus64 51 }

hmWanMbus64VIF17		OBJECT-TYPE
			SYNTAX	INTEGER
			MAX-ACCESS	read-only
			STATUS	current
			::= { hmWanMbus64 52 }

hmWanMbus64Value17		OBJECT-TYPE
			SYNTAX	INTEGER
			MAX-ACCESS	read-only
			STATUS	current
			::= { hmWanMbus64 53 }

hmWanMbus64VIF18		OBJECT-TYPE
			SYNTAX	INTEGER
			MAX-ACCESS	read-only
			STATUS	current
			::= { hmWanMbus64 54 }

hmWanMbus64Value18		OBJECT-TYPE
			SYNTAX	INTEGER
			MAX-ACCESS	read-only
			STATUS	current
			::= { hmWanMbus64 55 }

hmWanMbus64VIF19		OBJECT-TYPE
			SYNTAX	INTEGER
			MAX-ACCESS	read-only
			STATUS	current
			::= { hmWanMbus64 56 }

hmWanMbus64Value19		OBJECT-TYPE
			SYNTAX	INTEGER
			MAX-ACCESS	read-only
			STATUS	current
			::= { hmWanMbus64 57 }

hmWanMbus64VIF1A		OBJECT-TYPE
			SYNTAX	INTEGER
			MAX-ACCESS	read-only
			STATUS	current
			::= { hmWanMbus64 58 }

hmWanMbus64Value1A		OBJECT-TYPE
			SYNTAX	INTEGER
			MAX-ACCESS	read-only
			STATUS	current
			::= { hmWanMbus64 59 }

hmWanMbus64VIF1B		OBJECT-TYPE
			SYNTAX	INTEGER
			MAX-ACCESS	read-only
			STATUS	current
			::= { hmWanMbus64 60 }

hmWanMbus64Value1B		OBJECT-TYPE
			SYNTAX	INTEGER
			MAX-ACCESS	read-only
			STATUS	current
			::= { hmWanMbus64 61 }

hmWanMbus64VIF1C		OBJECT-TYPE
			SYNTAX	INTEGER
			MAX-ACCESS	read-only
			STATUS	current
			::= { hmWanMbus64 62 }

hmWanMbus64Value1C		OBJECT-TYPE
			SYNTAX	INTEGER
			MAX-ACCESS	read-only
			STATUS	current
			::= { hmWanMbus64 63 }

hmWanMbus64VIF1D		OBJECT-TYPE
			SYNTAX	INTEGER
			MAX-ACCESS	read-only
			STATUS	current
			::= { hmWanMbus64 64 }

hmWanMbus64Value1D		OBJECT-TYPE
			SYNTAX	INTEGER
			MAX-ACCESS	read-only
			STATUS	current
			::= { hmWanMbus64 65 }

hmWanMbus64VIF1E		OBJECT-TYPE
			SYNTAX	INTEGER
			MAX-ACCESS	read-only
			STATUS	current
			::= { hmWanMbus64 66 }

hmWanMbus64Value1E		OBJECT-TYPE
			SYNTAX	INTEGER
			MAX-ACCESS	read-only
			STATUS	current
			::= { hmWanMbus64 67 }

hmWanMbus64VIF1F		OBJECT-TYPE
			SYNTAX	INTEGER
			MAX-ACCESS	read-only
			STATUS	current
			::= { hmWanMbus64 68 }

hmWanMbus64Value1F		OBJECT-TYPE
			SYNTAX	INTEGER
			MAX-ACCESS	read-only
			STATUS	current
			::= { hmWanMbus64 69 }

hmWanMbus64VIF20		OBJECT-TYPE
			SYNTAX	INTEGER
			MAX-ACCESS	read-only
			STATUS	current
			::= { hmWanMbus64 70 }

hmWanMbus64Value20		OBJECT-TYPE
			SYNTAX	INTEGER
			MAX-ACCESS	read-only
			STATUS	current
			::= { hmWanMbus64 71 }

hmWanMbus64VIF21		OBJECT-TYPE
			SYNTAX	INTEGER
			MAX-ACCESS	read-only
			STATUS	current
			::= { hmWanMbus64 72 }

hmWanMbus64Value21		OBJECT-TYPE
			SYNTAX	INTEGER
			MAX-ACCESS	read-only
			STATUS	current
			::= { hmWanMbus64 73 }

hmWanMbus64VIF22		OBJECT-TYPE
			SYNTAX	INTEGER
			MAX-ACCESS	read-only
			STATUS	current
			::= { hmWanMbus64 74 }

hmWanMbus64Value22		OBJECT-TYPE
			SYNTAX	INTEGER
			MAX-ACCESS	read-only
			STATUS	current
			::= { hmWanMbus64 75 }

hmWanMbus64VIF23		OBJECT-TYPE
			SYNTAX	INTEGER
			MAX-ACCESS	read-only
			STATUS	current
			::= { hmWanMbus64 76 }

hmWanMbus64Value23		OBJECT-TYPE
			SYNTAX	INTEGER
			MAX-ACCESS	read-only
			STATUS	current
			::= { hmWanMbus64 77 }

hmWanMbus64VIF24		OBJECT-TYPE
			SYNTAX	INTEGER
			MAX-ACCESS	read-only
			STATUS	current
			::= { hmWanMbus64 78 }

hmWanMbus64Value24		OBJECT-TYPE
			SYNTAX	INTEGER
			MAX-ACCESS	read-only
			STATUS	current
			::= { hmWanMbus64 79 }

hmWanMbus64VIF25		OBJECT-TYPE
			SYNTAX	INTEGER
			MAX-ACCESS	read-only
			STATUS	current
			::= { hmWanMbus64 80 }

hmWanMbus64Value25		OBJECT-TYPE
			SYNTAX	INTEGER
			MAX-ACCESS	read-only
			STATUS	current
			::= { hmWanMbus64 81 }

hmWanMbus64VIF26		OBJECT-TYPE
			SYNTAX	INTEGER
			MAX-ACCESS	read-only
			STATUS	current
			::= { hmWanMbus64 82 }

hmWanMbus64Value26		OBJECT-TYPE
			SYNTAX	INTEGER
			MAX-ACCESS	read-only
			STATUS	current
			::= { hmWanMbus64 83 }

hmWanMbus64VIF27		OBJECT-TYPE
			SYNTAX	INTEGER
			MAX-ACCESS	read-only
			STATUS	current
			::= { hmWanMbus64 84 }

hmWanMbus64Value27		OBJECT-TYPE
			SYNTAX	INTEGER
			MAX-ACCESS	read-only
			STATUS	current
			::= { hmWanMbus64 85 }

hmWanMbus64VIF28		OBJECT-TYPE
			SYNTAX	INTEGER
			MAX-ACCESS	read-only
			STATUS	current
			::= { hmWanMbus64 86 }

hmWanMbus64Value28		OBJECT-TYPE
			SYNTAX	INTEGER
			MAX-ACCESS	read-only
			STATUS	current
			::= { hmWanMbus64 87 }

hmWanMbus64VIF29		OBJECT-TYPE
			SYNTAX	INTEGER
			MAX-ACCESS	read-only
			STATUS	current
			::= { hmWanMbus64 88 }

hmWanMbus64Value29		OBJECT-TYPE
			SYNTAX	INTEGER
			MAX-ACCESS	read-only
			STATUS	current
			::= { hmWanMbus64 89 }

hmWanMbus64VIF2A		OBJECT-TYPE
			SYNTAX	INTEGER
			MAX-ACCESS	read-only
			STATUS	current
			::= { hmWanMbus64 90 }

hmWanMbus64Value2A		OBJECT-TYPE
			SYNTAX	INTEGER
			MAX-ACCESS	read-only
			STATUS	current
			::= { hmWanMbus64 91 }

hmWanMbus64VIF2B		OBJECT-TYPE
			SYNTAX	INTEGER
			MAX-ACCESS	read-only
			STATUS	current
			::= { hmWanMbus64 92 }

hmWanMbus64Value2B		OBJECT-TYPE
			SYNTAX	INTEGER
			MAX-ACCESS	read-only
			STATUS	current
			::= { hmWanMbus64 93 }

hmWanMbus64VIF2C		OBJECT-TYPE
			SYNTAX	INTEGER
			MAX-ACCESS	read-only
			STATUS	current
			::= { hmWanMbus64 94 }

hmWanMbus64Value2C		OBJECT-TYPE
			SYNTAX	INTEGER
			MAX-ACCESS	read-only
			STATUS	current
			::= { hmWanMbus64 95 }

hmWanMbus64VIF2D		OBJECT-TYPE
			SYNTAX	INTEGER
			MAX-ACCESS	read-only
			STATUS	current
			::= { hmWanMbus64 96 }

hmWanMbus64Value2D		OBJECT-TYPE
			SYNTAX	INTEGER
			MAX-ACCESS	read-only
			STATUS	current
			::= { hmWanMbus64 97 }

hmWanMbus64VIF2E		OBJECT-TYPE
			SYNTAX	INTEGER
			MAX-ACCESS	read-only
			STATUS	current
			::= { hmWanMbus64 98 }

hmWanMbus64Value2E		OBJECT-TYPE
			SYNTAX	INTEGER
			MAX-ACCESS	read-only
			STATUS	current
			::= { hmWanMbus64 99 }

hmWanMbus64VIF2F		OBJECT-TYPE
			SYNTAX	INTEGER
			MAX-ACCESS	read-only
			STATUS	current
			::= { hmWanMbus64 100 }

hmWanMbus64Value2F		OBJECT-TYPE
			SYNTAX	INTEGER
			MAX-ACCESS	read-only
			STATUS	current
			::= { hmWanMbus64 101 }

hmWanMbus65			OBJECT IDENTIFIER ::= { hmWanMbus 101 }

hmWanMbus65IdNumber		OBJECT-TYPE
			SYNTAX	Gauge32
			MAX-ACCESS	read-only
			STATUS	current
			::= { hmWanMbus65 1 }

hmWanMbus65Manufacturer	OBJECT-TYPE
			SYNTAX	Gauge32
			MAX-ACCESS	read-only
			STATUS	current
			::= { hmWanMbus65 2 }

hmWanMbus65Version		OBJECT-TYPE
			SYNTAX	Gauge32
			MAX-ACCESS	read-only
			STATUS	current
			::= { hmWanMbus65 3 }

hmWanMbus65Medium		OBJECT-TYPE
			SYNTAX	Gauge32
			MAX-ACCESS	read-only
			STATUS	current
			::= { hmWanMbus65 4 }

hmWanMbus65Status		OBJECT-TYPE
			SYNTAX	Gauge32
			MAX-ACCESS	read-only
			STATUS	current
			::= { hmWanMbus65 5 }

hmWanMbus65VIF00		OBJECT-TYPE
			SYNTAX	INTEGER
			MAX-ACCESS	read-only
			STATUS	current
			::= { hmWanMbus65 6 }

hmWanMbus65Value00		OBJECT-TYPE
			SYNTAX	INTEGER
			MAX-ACCESS	read-only
			STATUS	current
			::= { hmWanMbus65 7 }

hmWanMbus65VIF01		OBJECT-TYPE
			SYNTAX	INTEGER
			MAX-ACCESS	read-only
			STATUS	current
			::= { hmWanMbus65 8 }

hmWanMbus65Value01		OBJECT-TYPE
			SYNTAX	INTEGER
			MAX-ACCESS	read-only
			STATUS	current
			::= { hmWanMbus65 9 }

hmWanMbus65VIF02		OBJECT-TYPE
			SYNTAX	INTEGER
			MAX-ACCESS	read-only
			STATUS	current
			::= { hmWanMbus65 10 }

hmWanMbus65Value02		OBJECT-TYPE
			SYNTAX	INTEGER
			MAX-ACCESS	read-only
			STATUS	current
			::= { hmWanMbus65 11 }

hmWanMbus65VIF03		OBJECT-TYPE
			SYNTAX	INTEGER
			MAX-ACCESS	read-only
			STATUS	current
			::= { hmWanMbus65 12 }

hmWanMbus65Value03		OBJECT-TYPE
			SYNTAX	INTEGER
			MAX-ACCESS	read-only
			STATUS	current
			::= { hmWanMbus65 13 }

hmWanMbus65VIF04		OBJECT-TYPE
			SYNTAX	INTEGER
			MAX-ACCESS	read-only
			STATUS	current
			::= { hmWanMbus65 14 }

hmWanMbus65Value04		OBJECT-TYPE
			SYNTAX	INTEGER
			MAX-ACCESS	read-only
			STATUS	current
			::= { hmWanMbus65 15 }

hmWanMbus65VIF05		OBJECT-TYPE
			SYNTAX	INTEGER
			MAX-ACCESS	read-only
			STATUS	current
			::= { hmWanMbus65 16 }

hmWanMbus65Value05		OBJECT-TYPE
			SYNTAX	INTEGER
			MAX-ACCESS	read-only
			STATUS	current
			::= { hmWanMbus65 17 }

hmWanMbus65VIF06		OBJECT-TYPE
			SYNTAX	INTEGER
			MAX-ACCESS	read-only
			STATUS	current
			::= { hmWanMbus65 18 }

hmWanMbus65Value06		OBJECT-TYPE
			SYNTAX	INTEGER
			MAX-ACCESS	read-only
			STATUS	current
			::= { hmWanMbus65 19 }

hmWanMbus65VIF07		OBJECT-TYPE
			SYNTAX	INTEGER
			MAX-ACCESS	read-only
			STATUS	current
			::= { hmWanMbus65 20 }

hmWanMbus65Value07		OBJECT-TYPE
			SYNTAX	INTEGER
			MAX-ACCESS	read-only
			STATUS	current
			::= { hmWanMbus65 21 }

hmWanMbus65VIF08		OBJECT-TYPE
			SYNTAX	INTEGER
			MAX-ACCESS	read-only
			STATUS	current
			::= { hmWanMbus65 22 }

hmWanMbus65Value08		OBJECT-TYPE
			SYNTAX	INTEGER
			MAX-ACCESS	read-only
			STATUS	current
			::= { hmWanMbus65 23 }

hmWanMbus65VIF09		OBJECT-TYPE
			SYNTAX	INTEGER
			MAX-ACCESS	read-only
			STATUS	current
			::= { hmWanMbus65 24 }

hmWanMbus65Value09		OBJECT-TYPE
			SYNTAX	INTEGER
			MAX-ACCESS	read-only
			STATUS	current
			::= { hmWanMbus65 25 }

hmWanMbus65VIF0A		OBJECT-TYPE
			SYNTAX	INTEGER
			MAX-ACCESS	read-only
			STATUS	current
			::= { hmWanMbus65 26 }

hmWanMbus65Value0A		OBJECT-TYPE
			SYNTAX	INTEGER
			MAX-ACCESS	read-only
			STATUS	current
			::= { hmWanMbus65 27 }

hmWanMbus65VIF0B		OBJECT-TYPE
			SYNTAX	INTEGER
			MAX-ACCESS	read-only
			STATUS	current
			::= { hmWanMbus65 28 }

hmWanMbus65Value0B		OBJECT-TYPE
			SYNTAX	INTEGER
			MAX-ACCESS	read-only
			STATUS	current
			::= { hmWanMbus65 29 }

hmWanMbus65VIF0C		OBJECT-TYPE
			SYNTAX	INTEGER
			MAX-ACCESS	read-only
			STATUS	current
			::= { hmWanMbus65 30 }

hmWanMbus65Value0C		OBJECT-TYPE
			SYNTAX	INTEGER
			MAX-ACCESS	read-only
			STATUS	current
			::= { hmWanMbus65 31 }

hmWanMbus65VIF0D		OBJECT-TYPE
			SYNTAX	INTEGER
			MAX-ACCESS	read-only
			STATUS	current
			::= { hmWanMbus65 32 }

hmWanMbus65Value0D		OBJECT-TYPE
			SYNTAX	INTEGER
			MAX-ACCESS	read-only
			STATUS	current
			::= { hmWanMbus65 33 }

hmWanMbus65VIF0E		OBJECT-TYPE
			SYNTAX	INTEGER
			MAX-ACCESS	read-only
			STATUS	current
			::= { hmWanMbus65 34 }

hmWanMbus65Value0E		OBJECT-TYPE
			SYNTAX	INTEGER
			MAX-ACCESS	read-only
			STATUS	current
			::= { hmWanMbus65 35 }

hmWanMbus65VIF0F		OBJECT-TYPE
			SYNTAX	INTEGER
			MAX-ACCESS	read-only
			STATUS	current
			::= { hmWanMbus65 36 }

hmWanMbus65Value0F		OBJECT-TYPE
			SYNTAX	INTEGER
			MAX-ACCESS	read-only
			STATUS	current
			::= { hmWanMbus65 37 }

hmWanMbus65VIF10		OBJECT-TYPE
			SYNTAX	INTEGER
			MAX-ACCESS	read-only
			STATUS	current
			::= { hmWanMbus65 38 }

hmWanMbus65Value10		OBJECT-TYPE
			SYNTAX	INTEGER
			MAX-ACCESS	read-only
			STATUS	current
			::= { hmWanMbus65 39 }

hmWanMbus65VIF11		OBJECT-TYPE
			SYNTAX	INTEGER
			MAX-ACCESS	read-only
			STATUS	current
			::= { hmWanMbus65 40 }

hmWanMbus65Value11		OBJECT-TYPE
			SYNTAX	INTEGER
			MAX-ACCESS	read-only
			STATUS	current
			::= { hmWanMbus65 41 }

hmWanMbus65VIF12		OBJECT-TYPE
			SYNTAX	INTEGER
			MAX-ACCESS	read-only
			STATUS	current
			::= { hmWanMbus65 42 }

hmWanMbus65Value12		OBJECT-TYPE
			SYNTAX	INTEGER
			MAX-ACCESS	read-only
			STATUS	current
			::= { hmWanMbus65 43 }

hmWanMbus65VIF13		OBJECT-TYPE
			SYNTAX	INTEGER
			MAX-ACCESS	read-only
			STATUS	current
			::= { hmWanMbus65 44 }

hmWanMbus65Value13		OBJECT-TYPE
			SYNTAX	INTEGER
			MAX-ACCESS	read-only
			STATUS	current
			::= { hmWanMbus65 45 }

hmWanMbus65VIF14		OBJECT-TYPE
			SYNTAX	INTEGER
			MAX-ACCESS	read-only
			STATUS	current
			::= { hmWanMbus65 46 }

hmWanMbus65Value14		OBJECT-TYPE
			SYNTAX	INTEGER
			MAX-ACCESS	read-only
			STATUS	current
			::= { hmWanMbus65 47 }

hmWanMbus65VIF15		OBJECT-TYPE
			SYNTAX	INTEGER
			MAX-ACCESS	read-only
			STATUS	current
			::= { hmWanMbus65 48 }

hmWanMbus65Value15		OBJECT-TYPE
			SYNTAX	INTEGER
			MAX-ACCESS	read-only
			STATUS	current
			::= { hmWanMbus65 49 }

hmWanMbus65VIF16		OBJECT-TYPE
			SYNTAX	INTEGER
			MAX-ACCESS	read-only
			STATUS	current
			::= { hmWanMbus65 50 }

hmWanMbus65Value16		OBJECT-TYPE
			SYNTAX	INTEGER
			MAX-ACCESS	read-only
			STATUS	current
			::= { hmWanMbus65 51 }

hmWanMbus65VIF17		OBJECT-TYPE
			SYNTAX	INTEGER
			MAX-ACCESS	read-only
			STATUS	current
			::= { hmWanMbus65 52 }

hmWanMbus65Value17		OBJECT-TYPE
			SYNTAX	INTEGER
			MAX-ACCESS	read-only
			STATUS	current
			::= { hmWanMbus65 53 }

hmWanMbus65VIF18		OBJECT-TYPE
			SYNTAX	INTEGER
			MAX-ACCESS	read-only
			STATUS	current
			::= { hmWanMbus65 54 }

hmWanMbus65Value18		OBJECT-TYPE
			SYNTAX	INTEGER
			MAX-ACCESS	read-only
			STATUS	current
			::= { hmWanMbus65 55 }

hmWanMbus65VIF19		OBJECT-TYPE
			SYNTAX	INTEGER
			MAX-ACCESS	read-only
			STATUS	current
			::= { hmWanMbus65 56 }

hmWanMbus65Value19		OBJECT-TYPE
			SYNTAX	INTEGER
			MAX-ACCESS	read-only
			STATUS	current
			::= { hmWanMbus65 57 }

hmWanMbus65VIF1A		OBJECT-TYPE
			SYNTAX	INTEGER
			MAX-ACCESS	read-only
			STATUS	current
			::= { hmWanMbus65 58 }

hmWanMbus65Value1A		OBJECT-TYPE
			SYNTAX	INTEGER
			MAX-ACCESS	read-only
			STATUS	current
			::= { hmWanMbus65 59 }

hmWanMbus65VIF1B		OBJECT-TYPE
			SYNTAX	INTEGER
			MAX-ACCESS	read-only
			STATUS	current
			::= { hmWanMbus65 60 }

hmWanMbus65Value1B		OBJECT-TYPE
			SYNTAX	INTEGER
			MAX-ACCESS	read-only
			STATUS	current
			::= { hmWanMbus65 61 }

hmWanMbus65VIF1C		OBJECT-TYPE
			SYNTAX	INTEGER
			MAX-ACCESS	read-only
			STATUS	current
			::= { hmWanMbus65 62 }

hmWanMbus65Value1C		OBJECT-TYPE
			SYNTAX	INTEGER
			MAX-ACCESS	read-only
			STATUS	current
			::= { hmWanMbus65 63 }

hmWanMbus65VIF1D		OBJECT-TYPE
			SYNTAX	INTEGER
			MAX-ACCESS	read-only
			STATUS	current
			::= { hmWanMbus65 64 }

hmWanMbus65Value1D		OBJECT-TYPE
			SYNTAX	INTEGER
			MAX-ACCESS	read-only
			STATUS	current
			::= { hmWanMbus65 65 }

hmWanMbus65VIF1E		OBJECT-TYPE
			SYNTAX	INTEGER
			MAX-ACCESS	read-only
			STATUS	current
			::= { hmWanMbus65 66 }

hmWanMbus65Value1E		OBJECT-TYPE
			SYNTAX	INTEGER
			MAX-ACCESS	read-only
			STATUS	current
			::= { hmWanMbus65 67 }

hmWanMbus65VIF1F		OBJECT-TYPE
			SYNTAX	INTEGER
			MAX-ACCESS	read-only
			STATUS	current
			::= { hmWanMbus65 68 }

hmWanMbus65Value1F		OBJECT-TYPE
			SYNTAX	INTEGER
			MAX-ACCESS	read-only
			STATUS	current
			::= { hmWanMbus65 69 }

hmWanMbus65VIF20		OBJECT-TYPE
			SYNTAX	INTEGER
			MAX-ACCESS	read-only
			STATUS	current
			::= { hmWanMbus65 70 }

hmWanMbus65Value20		OBJECT-TYPE
			SYNTAX	INTEGER
			MAX-ACCESS	read-only
			STATUS	current
			::= { hmWanMbus65 71 }

hmWanMbus65VIF21		OBJECT-TYPE
			SYNTAX	INTEGER
			MAX-ACCESS	read-only
			STATUS	current
			::= { hmWanMbus65 72 }

hmWanMbus65Value21		OBJECT-TYPE
			SYNTAX	INTEGER
			MAX-ACCESS	read-only
			STATUS	current
			::= { hmWanMbus65 73 }

hmWanMbus65VIF22		OBJECT-TYPE
			SYNTAX	INTEGER
			MAX-ACCESS	read-only
			STATUS	current
			::= { hmWanMbus65 74 }

hmWanMbus65Value22		OBJECT-TYPE
			SYNTAX	INTEGER
			MAX-ACCESS	read-only
			STATUS	current
			::= { hmWanMbus65 75 }

hmWanMbus65VIF23		OBJECT-TYPE
			SYNTAX	INTEGER
			MAX-ACCESS	read-only
			STATUS	current
			::= { hmWanMbus65 76 }

hmWanMbus65Value23		OBJECT-TYPE
			SYNTAX	INTEGER
			MAX-ACCESS	read-only
			STATUS	current
			::= { hmWanMbus65 77 }

hmWanMbus65VIF24		OBJECT-TYPE
			SYNTAX	INTEGER
			MAX-ACCESS	read-only
			STATUS	current
			::= { hmWanMbus65 78 }

hmWanMbus65Value24		OBJECT-TYPE
			SYNTAX	INTEGER
			MAX-ACCESS	read-only
			STATUS	current
			::= { hmWanMbus65 79 }

hmWanMbus65VIF25		OBJECT-TYPE
			SYNTAX	INTEGER
			MAX-ACCESS	read-only
			STATUS	current
			::= { hmWanMbus65 80 }

hmWanMbus65Value25		OBJECT-TYPE
			SYNTAX	INTEGER
			MAX-ACCESS	read-only
			STATUS	current
			::= { hmWanMbus65 81 }

hmWanMbus65VIF26		OBJECT-TYPE
			SYNTAX	INTEGER
			MAX-ACCESS	read-only
			STATUS	current
			::= { hmWanMbus65 82 }

hmWanMbus65Value26		OBJECT-TYPE
			SYNTAX	INTEGER
			MAX-ACCESS	read-only
			STATUS	current
			::= { hmWanMbus65 83 }

hmWanMbus65VIF27		OBJECT-TYPE
			SYNTAX	INTEGER
			MAX-ACCESS	read-only
			STATUS	current
			::= { hmWanMbus65 84 }

hmWanMbus65Value27		OBJECT-TYPE
			SYNTAX	INTEGER
			MAX-ACCESS	read-only
			STATUS	current
			::= { hmWanMbus65 85 }

hmWanMbus65VIF28		OBJECT-TYPE
			SYNTAX	INTEGER
			MAX-ACCESS	read-only
			STATUS	current
			::= { hmWanMbus65 86 }

hmWanMbus65Value28		OBJECT-TYPE
			SYNTAX	INTEGER
			MAX-ACCESS	read-only
			STATUS	current
			::= { hmWanMbus65 87 }

hmWanMbus65VIF29		OBJECT-TYPE
			SYNTAX	INTEGER
			MAX-ACCESS	read-only
			STATUS	current
			::= { hmWanMbus65 88 }

hmWanMbus65Value29		OBJECT-TYPE
			SYNTAX	INTEGER
			MAX-ACCESS	read-only
			STATUS	current
			::= { hmWanMbus65 89 }

hmWanMbus65VIF2A		OBJECT-TYPE
			SYNTAX	INTEGER
			MAX-ACCESS	read-only
			STATUS	current
			::= { hmWanMbus65 90 }

hmWanMbus65Value2A		OBJECT-TYPE
			SYNTAX	INTEGER
			MAX-ACCESS	read-only
			STATUS	current
			::= { hmWanMbus65 91 }

hmWanMbus65VIF2B		OBJECT-TYPE
			SYNTAX	INTEGER
			MAX-ACCESS	read-only
			STATUS	current
			::= { hmWanMbus65 92 }

hmWanMbus65Value2B		OBJECT-TYPE
			SYNTAX	INTEGER
			MAX-ACCESS	read-only
			STATUS	current
			::= { hmWanMbus65 93 }

hmWanMbus65VIF2C		OBJECT-TYPE
			SYNTAX	INTEGER
			MAX-ACCESS	read-only
			STATUS	current
			::= { hmWanMbus65 94 }

hmWanMbus65Value2C		OBJECT-TYPE
			SYNTAX	INTEGER
			MAX-ACCESS	read-only
			STATUS	current
			::= { hmWanMbus65 95 }

hmWanMbus65VIF2D		OBJECT-TYPE
			SYNTAX	INTEGER
			MAX-ACCESS	read-only
			STATUS	current
			::= { hmWanMbus65 96 }

hmWanMbus65Value2D		OBJECT-TYPE
			SYNTAX	INTEGER
			MAX-ACCESS	read-only
			STATUS	current
			::= { hmWanMbus65 97 }

hmWanMbus65VIF2E		OBJECT-TYPE
			SYNTAX	INTEGER
			MAX-ACCESS	read-only
			STATUS	current
			::= { hmWanMbus65 98 }

hmWanMbus65Value2E		OBJECT-TYPE
			SYNTAX	INTEGER
			MAX-ACCESS	read-only
			STATUS	current
			::= { hmWanMbus65 99 }

hmWanMbus65VIF2F		OBJECT-TYPE
			SYNTAX	INTEGER
			MAX-ACCESS	read-only
			STATUS	current
			::= { hmWanMbus65 100 }

hmWanMbus65Value2F		OBJECT-TYPE
			SYNTAX	INTEGER
			MAX-ACCESS	read-only
			STATUS	current
			::= { hmWanMbus65 101 }

hmWanMbus66			OBJECT IDENTIFIER ::= { hmWanMbus 102 }

hmWanMbus66IdNumber		OBJECT-TYPE
			SYNTAX	Gauge32
			MAX-ACCESS	read-only
			STATUS	current
			::= { hmWanMbus66 1 }

hmWanMbus66Manufacturer	OBJECT-TYPE
			SYNTAX	Gauge32
			MAX-ACCESS	read-only
			STATUS	current
			::= { hmWanMbus66 2 }

hmWanMbus66Version		OBJECT-TYPE
			SYNTAX	Gauge32
			MAX-ACCESS	read-only
			STATUS	current
			::= { hmWanMbus66 3 }

hmWanMbus66Medium		OBJECT-TYPE
			SYNTAX	Gauge32
			MAX-ACCESS	read-only
			STATUS	current
			::= { hmWanMbus66 4 }

hmWanMbus66Status		OBJECT-TYPE
			SYNTAX	Gauge32
			MAX-ACCESS	read-only
			STATUS	current
			::= { hmWanMbus66 5 }

hmWanMbus66VIF00		OBJECT-TYPE
			SYNTAX	INTEGER
			MAX-ACCESS	read-only
			STATUS	current
			::= { hmWanMbus66 6 }

hmWanMbus66Value00		OBJECT-TYPE
			SYNTAX	INTEGER
			MAX-ACCESS	read-only
			STATUS	current
			::= { hmWanMbus66 7 }

hmWanMbus66VIF01		OBJECT-TYPE
			SYNTAX	INTEGER
			MAX-ACCESS	read-only
			STATUS	current
			::= { hmWanMbus66 8 }

hmWanMbus66Value01		OBJECT-TYPE
			SYNTAX	INTEGER
			MAX-ACCESS	read-only
			STATUS	current
			::= { hmWanMbus66 9 }

hmWanMbus66VIF02		OBJECT-TYPE
			SYNTAX	INTEGER
			MAX-ACCESS	read-only
			STATUS	current
			::= { hmWanMbus66 10 }

hmWanMbus66Value02		OBJECT-TYPE
			SYNTAX	INTEGER
			MAX-ACCESS	read-only
			STATUS	current
			::= { hmWanMbus66 11 }

hmWanMbus66VIF03		OBJECT-TYPE
			SYNTAX	INTEGER
			MAX-ACCESS	read-only
			STATUS	current
			::= { hmWanMbus66 12 }

hmWanMbus66Value03		OBJECT-TYPE
			SYNTAX	INTEGER
			MAX-ACCESS	read-only
			STATUS	current
			::= { hmWanMbus66 13 }

hmWanMbus66VIF04		OBJECT-TYPE
			SYNTAX	INTEGER
			MAX-ACCESS	read-only
			STATUS	current
			::= { hmWanMbus66 14 }

hmWanMbus66Value04		OBJECT-TYPE
			SYNTAX	INTEGER
			MAX-ACCESS	read-only
			STATUS	current
			::= { hmWanMbus66 15 }

hmWanMbus66VIF05		OBJECT-TYPE
			SYNTAX	INTEGER
			MAX-ACCESS	read-only
			STATUS	current
			::= { hmWanMbus66 16 }

hmWanMbus66Value05		OBJECT-TYPE
			SYNTAX	INTEGER
			MAX-ACCESS	read-only
			STATUS	current
			::= { hmWanMbus66 17 }

hmWanMbus66VIF06		OBJECT-TYPE
			SYNTAX	INTEGER
			MAX-ACCESS	read-only
			STATUS	current
			::= { hmWanMbus66 18 }

hmWanMbus66Value06		OBJECT-TYPE
			SYNTAX	INTEGER
			MAX-ACCESS	read-only
			STATUS	current
			::= { hmWanMbus66 19 }

hmWanMbus66VIF07		OBJECT-TYPE
			SYNTAX	INTEGER
			MAX-ACCESS	read-only
			STATUS	current
			::= { hmWanMbus66 20 }

hmWanMbus66Value07		OBJECT-TYPE
			SYNTAX	INTEGER
			MAX-ACCESS	read-only
			STATUS	current
			::= { hmWanMbus66 21 }

hmWanMbus66VIF08		OBJECT-TYPE
			SYNTAX	INTEGER
			MAX-ACCESS	read-only
			STATUS	current
			::= { hmWanMbus66 22 }

hmWanMbus66Value08		OBJECT-TYPE
			SYNTAX	INTEGER
			MAX-ACCESS	read-only
			STATUS	current
			::= { hmWanMbus66 23 }

hmWanMbus66VIF09		OBJECT-TYPE
			SYNTAX	INTEGER
			MAX-ACCESS	read-only
			STATUS	current
			::= { hmWanMbus66 24 }

hmWanMbus66Value09		OBJECT-TYPE
			SYNTAX	INTEGER
			MAX-ACCESS	read-only
			STATUS	current
			::= { hmWanMbus66 25 }

hmWanMbus66VIF0A		OBJECT-TYPE
			SYNTAX	INTEGER
			MAX-ACCESS	read-only
			STATUS	current
			::= { hmWanMbus66 26 }

hmWanMbus66Value0A		OBJECT-TYPE
			SYNTAX	INTEGER
			MAX-ACCESS	read-only
			STATUS	current
			::= { hmWanMbus66 27 }

hmWanMbus66VIF0B		OBJECT-TYPE
			SYNTAX	INTEGER
			MAX-ACCESS	read-only
			STATUS	current
			::= { hmWanMbus66 28 }

hmWanMbus66Value0B		OBJECT-TYPE
			SYNTAX	INTEGER
			MAX-ACCESS	read-only
			STATUS	current
			::= { hmWanMbus66 29 }

hmWanMbus66VIF0C		OBJECT-TYPE
			SYNTAX	INTEGER
			MAX-ACCESS	read-only
			STATUS	current
			::= { hmWanMbus66 30 }

hmWanMbus66Value0C		OBJECT-TYPE
			SYNTAX	INTEGER
			MAX-ACCESS	read-only
			STATUS	current
			::= { hmWanMbus66 31 }

hmWanMbus66VIF0D		OBJECT-TYPE
			SYNTAX	INTEGER
			MAX-ACCESS	read-only
			STATUS	current
			::= { hmWanMbus66 32 }

hmWanMbus66Value0D		OBJECT-TYPE
			SYNTAX	INTEGER
			MAX-ACCESS	read-only
			STATUS	current
			::= { hmWanMbus66 33 }

hmWanMbus66VIF0E		OBJECT-TYPE
			SYNTAX	INTEGER
			MAX-ACCESS	read-only
			STATUS	current
			::= { hmWanMbus66 34 }

hmWanMbus66Value0E		OBJECT-TYPE
			SYNTAX	INTEGER
			MAX-ACCESS	read-only
			STATUS	current
			::= { hmWanMbus66 35 }

hmWanMbus66VIF0F		OBJECT-TYPE
			SYNTAX	INTEGER
			MAX-ACCESS	read-only
			STATUS	current
			::= { hmWanMbus66 36 }

hmWanMbus66Value0F		OBJECT-TYPE
			SYNTAX	INTEGER
			MAX-ACCESS	read-only
			STATUS	current
			::= { hmWanMbus66 37 }

hmWanMbus66VIF10		OBJECT-TYPE
			SYNTAX	INTEGER
			MAX-ACCESS	read-only
			STATUS	current
			::= { hmWanMbus66 38 }

hmWanMbus66Value10		OBJECT-TYPE
			SYNTAX	INTEGER
			MAX-ACCESS	read-only
			STATUS	current
			::= { hmWanMbus66 39 }

hmWanMbus66VIF11		OBJECT-TYPE
			SYNTAX	INTEGER
			MAX-ACCESS	read-only
			STATUS	current
			::= { hmWanMbus66 40 }

hmWanMbus66Value11		OBJECT-TYPE
			SYNTAX	INTEGER
			MAX-ACCESS	read-only
			STATUS	current
			::= { hmWanMbus66 41 }

hmWanMbus66VIF12		OBJECT-TYPE
			SYNTAX	INTEGER
			MAX-ACCESS	read-only
			STATUS	current
			::= { hmWanMbus66 42 }

hmWanMbus66Value12		OBJECT-TYPE
			SYNTAX	INTEGER
			MAX-ACCESS	read-only
			STATUS	current
			::= { hmWanMbus66 43 }

hmWanMbus66VIF13		OBJECT-TYPE
			SYNTAX	INTEGER
			MAX-ACCESS	read-only
			STATUS	current
			::= { hmWanMbus66 44 }

hmWanMbus66Value13		OBJECT-TYPE
			SYNTAX	INTEGER
			MAX-ACCESS	read-only
			STATUS	current
			::= { hmWanMbus66 45 }

hmWanMbus66VIF14		OBJECT-TYPE
			SYNTAX	INTEGER
			MAX-ACCESS	read-only
			STATUS	current
			::= { hmWanMbus66 46 }

hmWanMbus66Value14		OBJECT-TYPE
			SYNTAX	INTEGER
			MAX-ACCESS	read-only
			STATUS	current
			::= { hmWanMbus66 47 }

hmWanMbus66VIF15		OBJECT-TYPE
			SYNTAX	INTEGER
			MAX-ACCESS	read-only
			STATUS	current
			::= { hmWanMbus66 48 }

hmWanMbus66Value15		OBJECT-TYPE
			SYNTAX	INTEGER
			MAX-ACCESS	read-only
			STATUS	current
			::= { hmWanMbus66 49 }

hmWanMbus66VIF16		OBJECT-TYPE
			SYNTAX	INTEGER
			MAX-ACCESS	read-only
			STATUS	current
			::= { hmWanMbus66 50 }

hmWanMbus66Value16		OBJECT-TYPE
			SYNTAX	INTEGER
			MAX-ACCESS	read-only
			STATUS	current
			::= { hmWanMbus66 51 }

hmWanMbus66VIF17		OBJECT-TYPE
			SYNTAX	INTEGER
			MAX-ACCESS	read-only
			STATUS	current
			::= { hmWanMbus66 52 }

hmWanMbus66Value17		OBJECT-TYPE
			SYNTAX	INTEGER
			MAX-ACCESS	read-only
			STATUS	current
			::= { hmWanMbus66 53 }

hmWanMbus66VIF18		OBJECT-TYPE
			SYNTAX	INTEGER
			MAX-ACCESS	read-only
			STATUS	current
			::= { hmWanMbus66 54 }

hmWanMbus66Value18		OBJECT-TYPE
			SYNTAX	INTEGER
			MAX-ACCESS	read-only
			STATUS	current
			::= { hmWanMbus66 55 }

hmWanMbus66VIF19		OBJECT-TYPE
			SYNTAX	INTEGER
			MAX-ACCESS	read-only
			STATUS	current
			::= { hmWanMbus66 56 }

hmWanMbus66Value19		OBJECT-TYPE
			SYNTAX	INTEGER
			MAX-ACCESS	read-only
			STATUS	current
			::= { hmWanMbus66 57 }

hmWanMbus66VIF1A		OBJECT-TYPE
			SYNTAX	INTEGER
			MAX-ACCESS	read-only
			STATUS	current
			::= { hmWanMbus66 58 }

hmWanMbus66Value1A		OBJECT-TYPE
			SYNTAX	INTEGER
			MAX-ACCESS	read-only
			STATUS	current
			::= { hmWanMbus66 59 }

hmWanMbus66VIF1B		OBJECT-TYPE
			SYNTAX	INTEGER
			MAX-ACCESS	read-only
			STATUS	current
			::= { hmWanMbus66 60 }

hmWanMbus66Value1B		OBJECT-TYPE
			SYNTAX	INTEGER
			MAX-ACCESS	read-only
			STATUS	current
			::= { hmWanMbus66 61 }

hmWanMbus66VIF1C		OBJECT-TYPE
			SYNTAX	INTEGER
			MAX-ACCESS	read-only
			STATUS	current
			::= { hmWanMbus66 62 }

hmWanMbus66Value1C		OBJECT-TYPE
			SYNTAX	INTEGER
			MAX-ACCESS	read-only
			STATUS	current
			::= { hmWanMbus66 63 }

hmWanMbus66VIF1D		OBJECT-TYPE
			SYNTAX	INTEGER
			MAX-ACCESS	read-only
			STATUS	current
			::= { hmWanMbus66 64 }

hmWanMbus66Value1D		OBJECT-TYPE
			SYNTAX	INTEGER
			MAX-ACCESS	read-only
			STATUS	current
			::= { hmWanMbus66 65 }

hmWanMbus66VIF1E		OBJECT-TYPE
			SYNTAX	INTEGER
			MAX-ACCESS	read-only
			STATUS	current
			::= { hmWanMbus66 66 }

hmWanMbus66Value1E		OBJECT-TYPE
			SYNTAX	INTEGER
			MAX-ACCESS	read-only
			STATUS	current
			::= { hmWanMbus66 67 }

hmWanMbus66VIF1F		OBJECT-TYPE
			SYNTAX	INTEGER
			MAX-ACCESS	read-only
			STATUS	current
			::= { hmWanMbus66 68 }

hmWanMbus66Value1F		OBJECT-TYPE
			SYNTAX	INTEGER
			MAX-ACCESS	read-only
			STATUS	current
			::= { hmWanMbus66 69 }

hmWanMbus66VIF20		OBJECT-TYPE
			SYNTAX	INTEGER
			MAX-ACCESS	read-only
			STATUS	current
			::= { hmWanMbus66 70 }

hmWanMbus66Value20		OBJECT-TYPE
			SYNTAX	INTEGER
			MAX-ACCESS	read-only
			STATUS	current
			::= { hmWanMbus66 71 }

hmWanMbus66VIF21		OBJECT-TYPE
			SYNTAX	INTEGER
			MAX-ACCESS	read-only
			STATUS	current
			::= { hmWanMbus66 72 }

hmWanMbus66Value21		OBJECT-TYPE
			SYNTAX	INTEGER
			MAX-ACCESS	read-only
			STATUS	current
			::= { hmWanMbus66 73 }

hmWanMbus66VIF22		OBJECT-TYPE
			SYNTAX	INTEGER
			MAX-ACCESS	read-only
			STATUS	current
			::= { hmWanMbus66 74 }

hmWanMbus66Value22		OBJECT-TYPE
			SYNTAX	INTEGER
			MAX-ACCESS	read-only
			STATUS	current
			::= { hmWanMbus66 75 }

hmWanMbus66VIF23		OBJECT-TYPE
			SYNTAX	INTEGER
			MAX-ACCESS	read-only
			STATUS	current
			::= { hmWanMbus66 76 }

hmWanMbus66Value23		OBJECT-TYPE
			SYNTAX	INTEGER
			MAX-ACCESS	read-only
			STATUS	current
			::= { hmWanMbus66 77 }

hmWanMbus66VIF24		OBJECT-TYPE
			SYNTAX	INTEGER
			MAX-ACCESS	read-only
			STATUS	current
			::= { hmWanMbus66 78 }

hmWanMbus66Value24		OBJECT-TYPE
			SYNTAX	INTEGER
			MAX-ACCESS	read-only
			STATUS	current
			::= { hmWanMbus66 79 }

hmWanMbus66VIF25		OBJECT-TYPE
			SYNTAX	INTEGER
			MAX-ACCESS	read-only
			STATUS	current
			::= { hmWanMbus66 80 }

hmWanMbus66Value25		OBJECT-TYPE
			SYNTAX	INTEGER
			MAX-ACCESS	read-only
			STATUS	current
			::= { hmWanMbus66 81 }

hmWanMbus66VIF26		OBJECT-TYPE
			SYNTAX	INTEGER
			MAX-ACCESS	read-only
			STATUS	current
			::= { hmWanMbus66 82 }

hmWanMbus66Value26		OBJECT-TYPE
			SYNTAX	INTEGER
			MAX-ACCESS	read-only
			STATUS	current
			::= { hmWanMbus66 83 }

hmWanMbus66VIF27		OBJECT-TYPE
			SYNTAX	INTEGER
			MAX-ACCESS	read-only
			STATUS	current
			::= { hmWanMbus66 84 }

hmWanMbus66Value27		OBJECT-TYPE
			SYNTAX	INTEGER
			MAX-ACCESS	read-only
			STATUS	current
			::= { hmWanMbus66 85 }

hmWanMbus66VIF28		OBJECT-TYPE
			SYNTAX	INTEGER
			MAX-ACCESS	read-only
			STATUS	current
			::= { hmWanMbus66 86 }

hmWanMbus66Value28		OBJECT-TYPE
			SYNTAX	INTEGER
			MAX-ACCESS	read-only
			STATUS	current
			::= { hmWanMbus66 87 }

hmWanMbus66VIF29		OBJECT-TYPE
			SYNTAX	INTEGER
			MAX-ACCESS	read-only
			STATUS	current
			::= { hmWanMbus66 88 }

hmWanMbus66Value29		OBJECT-TYPE
			SYNTAX	INTEGER
			MAX-ACCESS	read-only
			STATUS	current
			::= { hmWanMbus66 89 }

hmWanMbus66VIF2A		OBJECT-TYPE
			SYNTAX	INTEGER
			MAX-ACCESS	read-only
			STATUS	current
			::= { hmWanMbus66 90 }

hmWanMbus66Value2A		OBJECT-TYPE
			SYNTAX	INTEGER
			MAX-ACCESS	read-only
			STATUS	current
			::= { hmWanMbus66 91 }

hmWanMbus66VIF2B		OBJECT-TYPE
			SYNTAX	INTEGER
			MAX-ACCESS	read-only
			STATUS	current
			::= { hmWanMbus66 92 }

hmWanMbus66Value2B		OBJECT-TYPE
			SYNTAX	INTEGER
			MAX-ACCESS	read-only
			STATUS	current
			::= { hmWanMbus66 93 }

hmWanMbus66VIF2C		OBJECT-TYPE
			SYNTAX	INTEGER
			MAX-ACCESS	read-only
			STATUS	current
			::= { hmWanMbus66 94 }

hmWanMbus66Value2C		OBJECT-TYPE
			SYNTAX	INTEGER
			MAX-ACCESS	read-only
			STATUS	current
			::= { hmWanMbus66 95 }

hmWanMbus66VIF2D		OBJECT-TYPE
			SYNTAX	INTEGER
			MAX-ACCESS	read-only
			STATUS	current
			::= { hmWanMbus66 96 }

hmWanMbus66Value2D		OBJECT-TYPE
			SYNTAX	INTEGER
			MAX-ACCESS	read-only
			STATUS	current
			::= { hmWanMbus66 97 }

hmWanMbus66VIF2E		OBJECT-TYPE
			SYNTAX	INTEGER
			MAX-ACCESS	read-only
			STATUS	current
			::= { hmWanMbus66 98 }

hmWanMbus66Value2E		OBJECT-TYPE
			SYNTAX	INTEGER
			MAX-ACCESS	read-only
			STATUS	current
			::= { hmWanMbus66 99 }

hmWanMbus66VIF2F		OBJECT-TYPE
			SYNTAX	INTEGER
			MAX-ACCESS	read-only
			STATUS	current
			::= { hmWanMbus66 100 }

hmWanMbus66Value2F		OBJECT-TYPE
			SYNTAX	INTEGER
			MAX-ACCESS	read-only
			STATUS	current
			::= { hmWanMbus66 101 }

hmWanMbus67			OBJECT IDENTIFIER ::= { hmWanMbus 103 }

hmWanMbus67IdNumber		OBJECT-TYPE
			SYNTAX	Gauge32
			MAX-ACCESS	read-only
			STATUS	current
			::= { hmWanMbus67 1 }

hmWanMbus67Manufacturer	OBJECT-TYPE
			SYNTAX	Gauge32
			MAX-ACCESS	read-only
			STATUS	current
			::= { hmWanMbus67 2 }

hmWanMbus67Version		OBJECT-TYPE
			SYNTAX	Gauge32
			MAX-ACCESS	read-only
			STATUS	current
			::= { hmWanMbus67 3 }

hmWanMbus67Medium		OBJECT-TYPE
			SYNTAX	Gauge32
			MAX-ACCESS	read-only
			STATUS	current
			::= { hmWanMbus67 4 }

hmWanMbus67Status		OBJECT-TYPE
			SYNTAX	Gauge32
			MAX-ACCESS	read-only
			STATUS	current
			::= { hmWanMbus67 5 }

hmWanMbus67VIF00		OBJECT-TYPE
			SYNTAX	INTEGER
			MAX-ACCESS	read-only
			STATUS	current
			::= { hmWanMbus67 6 }

hmWanMbus67Value00		OBJECT-TYPE
			SYNTAX	INTEGER
			MAX-ACCESS	read-only
			STATUS	current
			::= { hmWanMbus67 7 }

hmWanMbus67VIF01		OBJECT-TYPE
			SYNTAX	INTEGER
			MAX-ACCESS	read-only
			STATUS	current
			::= { hmWanMbus67 8 }

hmWanMbus67Value01		OBJECT-TYPE
			SYNTAX	INTEGER
			MAX-ACCESS	read-only
			STATUS	current
			::= { hmWanMbus67 9 }

hmWanMbus67VIF02		OBJECT-TYPE
			SYNTAX	INTEGER
			MAX-ACCESS	read-only
			STATUS	current
			::= { hmWanMbus67 10 }

hmWanMbus67Value02		OBJECT-TYPE
			SYNTAX	INTEGER
			MAX-ACCESS	read-only
			STATUS	current
			::= { hmWanMbus67 11 }

hmWanMbus67VIF03		OBJECT-TYPE
			SYNTAX	INTEGER
			MAX-ACCESS	read-only
			STATUS	current
			::= { hmWanMbus67 12 }

hmWanMbus67Value03		OBJECT-TYPE
			SYNTAX	INTEGER
			MAX-ACCESS	read-only
			STATUS	current
			::= { hmWanMbus67 13 }

hmWanMbus67VIF04		OBJECT-TYPE
			SYNTAX	INTEGER
			MAX-ACCESS	read-only
			STATUS	current
			::= { hmWanMbus67 14 }

hmWanMbus67Value04		OBJECT-TYPE
			SYNTAX	INTEGER
			MAX-ACCESS	read-only
			STATUS	current
			::= { hmWanMbus67 15 }

hmWanMbus67VIF05		OBJECT-TYPE
			SYNTAX	INTEGER
			MAX-ACCESS	read-only
			STATUS	current
			::= { hmWanMbus67 16 }

hmWanMbus67Value05		OBJECT-TYPE
			SYNTAX	INTEGER
			MAX-ACCESS	read-only
			STATUS	current
			::= { hmWanMbus67 17 }

hmWanMbus67VIF06		OBJECT-TYPE
			SYNTAX	INTEGER
			MAX-ACCESS	read-only
			STATUS	current
			::= { hmWanMbus67 18 }

hmWanMbus67Value06		OBJECT-TYPE
			SYNTAX	INTEGER
			MAX-ACCESS	read-only
			STATUS	current
			::= { hmWanMbus67 19 }

hmWanMbus67VIF07		OBJECT-TYPE
			SYNTAX	INTEGER
			MAX-ACCESS	read-only
			STATUS	current
			::= { hmWanMbus67 20 }

hmWanMbus67Value07		OBJECT-TYPE
			SYNTAX	INTEGER
			MAX-ACCESS	read-only
			STATUS	current
			::= { hmWanMbus67 21 }

hmWanMbus67VIF08		OBJECT-TYPE
			SYNTAX	INTEGER
			MAX-ACCESS	read-only
			STATUS	current
			::= { hmWanMbus67 22 }

hmWanMbus67Value08		OBJECT-TYPE
			SYNTAX	INTEGER
			MAX-ACCESS	read-only
			STATUS	current
			::= { hmWanMbus67 23 }

hmWanMbus67VIF09		OBJECT-TYPE
			SYNTAX	INTEGER
			MAX-ACCESS	read-only
			STATUS	current
			::= { hmWanMbus67 24 }

hmWanMbus67Value09		OBJECT-TYPE
			SYNTAX	INTEGER
			MAX-ACCESS	read-only
			STATUS	current
			::= { hmWanMbus67 25 }

hmWanMbus67VIF0A		OBJECT-TYPE
			SYNTAX	INTEGER
			MAX-ACCESS	read-only
			STATUS	current
			::= { hmWanMbus67 26 }

hmWanMbus67Value0A		OBJECT-TYPE
			SYNTAX	INTEGER
			MAX-ACCESS	read-only
			STATUS	current
			::= { hmWanMbus67 27 }

hmWanMbus67VIF0B		OBJECT-TYPE
			SYNTAX	INTEGER
			MAX-ACCESS	read-only
			STATUS	current
			::= { hmWanMbus67 28 }

hmWanMbus67Value0B		OBJECT-TYPE
			SYNTAX	INTEGER
			MAX-ACCESS	read-only
			STATUS	current
			::= { hmWanMbus67 29 }

hmWanMbus67VIF0C		OBJECT-TYPE
			SYNTAX	INTEGER
			MAX-ACCESS	read-only
			STATUS	current
			::= { hmWanMbus67 30 }

hmWanMbus67Value0C		OBJECT-TYPE
			SYNTAX	INTEGER
			MAX-ACCESS	read-only
			STATUS	current
			::= { hmWanMbus67 31 }

hmWanMbus67VIF0D		OBJECT-TYPE
			SYNTAX	INTEGER
			MAX-ACCESS	read-only
			STATUS	current
			::= { hmWanMbus67 32 }

hmWanMbus67Value0D		OBJECT-TYPE
			SYNTAX	INTEGER
			MAX-ACCESS	read-only
			STATUS	current
			::= { hmWanMbus67 33 }

hmWanMbus67VIF0E		OBJECT-TYPE
			SYNTAX	INTEGER
			MAX-ACCESS	read-only
			STATUS	current
			::= { hmWanMbus67 34 }

hmWanMbus67Value0E		OBJECT-TYPE
			SYNTAX	INTEGER
			MAX-ACCESS	read-only
			STATUS	current
			::= { hmWanMbus67 35 }

hmWanMbus67VIF0F		OBJECT-TYPE
			SYNTAX	INTEGER
			MAX-ACCESS	read-only
			STATUS	current
			::= { hmWanMbus67 36 }

hmWanMbus67Value0F		OBJECT-TYPE
			SYNTAX	INTEGER
			MAX-ACCESS	read-only
			STATUS	current
			::= { hmWanMbus67 37 }

hmWanMbus67VIF10		OBJECT-TYPE
			SYNTAX	INTEGER
			MAX-ACCESS	read-only
			STATUS	current
			::= { hmWanMbus67 38 }

hmWanMbus67Value10		OBJECT-TYPE
			SYNTAX	INTEGER
			MAX-ACCESS	read-only
			STATUS	current
			::= { hmWanMbus67 39 }

hmWanMbus67VIF11		OBJECT-TYPE
			SYNTAX	INTEGER
			MAX-ACCESS	read-only
			STATUS	current
			::= { hmWanMbus67 40 }

hmWanMbus67Value11		OBJECT-TYPE
			SYNTAX	INTEGER
			MAX-ACCESS	read-only
			STATUS	current
			::= { hmWanMbus67 41 }

hmWanMbus67VIF12		OBJECT-TYPE
			SYNTAX	INTEGER
			MAX-ACCESS	read-only
			STATUS	current
			::= { hmWanMbus67 42 }

hmWanMbus67Value12		OBJECT-TYPE
			SYNTAX	INTEGER
			MAX-ACCESS	read-only
			STATUS	current
			::= { hmWanMbus67 43 }

hmWanMbus67VIF13		OBJECT-TYPE
			SYNTAX	INTEGER
			MAX-ACCESS	read-only
			STATUS	current
			::= { hmWanMbus67 44 }

hmWanMbus67Value13		OBJECT-TYPE
			SYNTAX	INTEGER
			MAX-ACCESS	read-only
			STATUS	current
			::= { hmWanMbus67 45 }

hmWanMbus67VIF14		OBJECT-TYPE
			SYNTAX	INTEGER
			MAX-ACCESS	read-only
			STATUS	current
			::= { hmWanMbus67 46 }

hmWanMbus67Value14		OBJECT-TYPE
			SYNTAX	INTEGER
			MAX-ACCESS	read-only
			STATUS	current
			::= { hmWanMbus67 47 }

hmWanMbus67VIF15		OBJECT-TYPE
			SYNTAX	INTEGER
			MAX-ACCESS	read-only
			STATUS	current
			::= { hmWanMbus67 48 }

hmWanMbus67Value15		OBJECT-TYPE
			SYNTAX	INTEGER
			MAX-ACCESS	read-only
			STATUS	current
			::= { hmWanMbus67 49 }

hmWanMbus67VIF16		OBJECT-TYPE
			SYNTAX	INTEGER
			MAX-ACCESS	read-only
			STATUS	current
			::= { hmWanMbus67 50 }

hmWanMbus67Value16		OBJECT-TYPE
			SYNTAX	INTEGER
			MAX-ACCESS	read-only
			STATUS	current
			::= { hmWanMbus67 51 }

hmWanMbus67VIF17		OBJECT-TYPE
			SYNTAX	INTEGER
			MAX-ACCESS	read-only
			STATUS	current
			::= { hmWanMbus67 52 }

hmWanMbus67Value17		OBJECT-TYPE
			SYNTAX	INTEGER
			MAX-ACCESS	read-only
			STATUS	current
			::= { hmWanMbus67 53 }

hmWanMbus67VIF18		OBJECT-TYPE
			SYNTAX	INTEGER
			MAX-ACCESS	read-only
			STATUS	current
			::= { hmWanMbus67 54 }

hmWanMbus67Value18		OBJECT-TYPE
			SYNTAX	INTEGER
			MAX-ACCESS	read-only
			STATUS	current
			::= { hmWanMbus67 55 }

hmWanMbus67VIF19		OBJECT-TYPE
			SYNTAX	INTEGER
			MAX-ACCESS	read-only
			STATUS	current
			::= { hmWanMbus67 56 }

hmWanMbus67Value19		OBJECT-TYPE
			SYNTAX	INTEGER
			MAX-ACCESS	read-only
			STATUS	current
			::= { hmWanMbus67 57 }

hmWanMbus67VIF1A		OBJECT-TYPE
			SYNTAX	INTEGER
			MAX-ACCESS	read-only
			STATUS	current
			::= { hmWanMbus67 58 }

hmWanMbus67Value1A		OBJECT-TYPE
			SYNTAX	INTEGER
			MAX-ACCESS	read-only
			STATUS	current
			::= { hmWanMbus67 59 }

hmWanMbus67VIF1B		OBJECT-TYPE
			SYNTAX	INTEGER
			MAX-ACCESS	read-only
			STATUS	current
			::= { hmWanMbus67 60 }

hmWanMbus67Value1B		OBJECT-TYPE
			SYNTAX	INTEGER
			MAX-ACCESS	read-only
			STATUS	current
			::= { hmWanMbus67 61 }

hmWanMbus67VIF1C		OBJECT-TYPE
			SYNTAX	INTEGER
			MAX-ACCESS	read-only
			STATUS	current
			::= { hmWanMbus67 62 }

hmWanMbus67Value1C		OBJECT-TYPE
			SYNTAX	INTEGER
			MAX-ACCESS	read-only
			STATUS	current
			::= { hmWanMbus67 63 }

hmWanMbus67VIF1D		OBJECT-TYPE
			SYNTAX	INTEGER
			MAX-ACCESS	read-only
			STATUS	current
			::= { hmWanMbus67 64 }

hmWanMbus67Value1D		OBJECT-TYPE
			SYNTAX	INTEGER
			MAX-ACCESS	read-only
			STATUS	current
			::= { hmWanMbus67 65 }

hmWanMbus67VIF1E		OBJECT-TYPE
			SYNTAX	INTEGER
			MAX-ACCESS	read-only
			STATUS	current
			::= { hmWanMbus67 66 }

hmWanMbus67Value1E		OBJECT-TYPE
			SYNTAX	INTEGER
			MAX-ACCESS	read-only
			STATUS	current
			::= { hmWanMbus67 67 }

hmWanMbus67VIF1F		OBJECT-TYPE
			SYNTAX	INTEGER
			MAX-ACCESS	read-only
			STATUS	current
			::= { hmWanMbus67 68 }

hmWanMbus67Value1F		OBJECT-TYPE
			SYNTAX	INTEGER
			MAX-ACCESS	read-only
			STATUS	current
			::= { hmWanMbus67 69 }

hmWanMbus67VIF20		OBJECT-TYPE
			SYNTAX	INTEGER
			MAX-ACCESS	read-only
			STATUS	current
			::= { hmWanMbus67 70 }

hmWanMbus67Value20		OBJECT-TYPE
			SYNTAX	INTEGER
			MAX-ACCESS	read-only
			STATUS	current
			::= { hmWanMbus67 71 }

hmWanMbus67VIF21		OBJECT-TYPE
			SYNTAX	INTEGER
			MAX-ACCESS	read-only
			STATUS	current
			::= { hmWanMbus67 72 }

hmWanMbus67Value21		OBJECT-TYPE
			SYNTAX	INTEGER
			MAX-ACCESS	read-only
			STATUS	current
			::= { hmWanMbus67 73 }

hmWanMbus67VIF22		OBJECT-TYPE
			SYNTAX	INTEGER
			MAX-ACCESS	read-only
			STATUS	current
			::= { hmWanMbus67 74 }

hmWanMbus67Value22		OBJECT-TYPE
			SYNTAX	INTEGER
			MAX-ACCESS	read-only
			STATUS	current
			::= { hmWanMbus67 75 }

hmWanMbus67VIF23		OBJECT-TYPE
			SYNTAX	INTEGER
			MAX-ACCESS	read-only
			STATUS	current
			::= { hmWanMbus67 76 }

hmWanMbus67Value23		OBJECT-TYPE
			SYNTAX	INTEGER
			MAX-ACCESS	read-only
			STATUS	current
			::= { hmWanMbus67 77 }

hmWanMbus67VIF24		OBJECT-TYPE
			SYNTAX	INTEGER
			MAX-ACCESS	read-only
			STATUS	current
			::= { hmWanMbus67 78 }

hmWanMbus67Value24		OBJECT-TYPE
			SYNTAX	INTEGER
			MAX-ACCESS	read-only
			STATUS	current
			::= { hmWanMbus67 79 }

hmWanMbus67VIF25		OBJECT-TYPE
			SYNTAX	INTEGER
			MAX-ACCESS	read-only
			STATUS	current
			::= { hmWanMbus67 80 }

hmWanMbus67Value25		OBJECT-TYPE
			SYNTAX	INTEGER
			MAX-ACCESS	read-only
			STATUS	current
			::= { hmWanMbus67 81 }

hmWanMbus67VIF26		OBJECT-TYPE
			SYNTAX	INTEGER
			MAX-ACCESS	read-only
			STATUS	current
			::= { hmWanMbus67 82 }

hmWanMbus67Value26		OBJECT-TYPE
			SYNTAX	INTEGER
			MAX-ACCESS	read-only
			STATUS	current
			::= { hmWanMbus67 83 }

hmWanMbus67VIF27		OBJECT-TYPE
			SYNTAX	INTEGER
			MAX-ACCESS	read-only
			STATUS	current
			::= { hmWanMbus67 84 }

hmWanMbus67Value27		OBJECT-TYPE
			SYNTAX	INTEGER
			MAX-ACCESS	read-only
			STATUS	current
			::= { hmWanMbus67 85 }

hmWanMbus67VIF28		OBJECT-TYPE
			SYNTAX	INTEGER
			MAX-ACCESS	read-only
			STATUS	current
			::= { hmWanMbus67 86 }

hmWanMbus67Value28		OBJECT-TYPE
			SYNTAX	INTEGER
			MAX-ACCESS	read-only
			STATUS	current
			::= { hmWanMbus67 87 }

hmWanMbus67VIF29		OBJECT-TYPE
			SYNTAX	INTEGER
			MAX-ACCESS	read-only
			STATUS	current
			::= { hmWanMbus67 88 }

hmWanMbus67Value29		OBJECT-TYPE
			SYNTAX	INTEGER
			MAX-ACCESS	read-only
			STATUS	current
			::= { hmWanMbus67 89 }

hmWanMbus67VIF2A		OBJECT-TYPE
			SYNTAX	INTEGER
			MAX-ACCESS	read-only
			STATUS	current
			::= { hmWanMbus67 90 }

hmWanMbus67Value2A		OBJECT-TYPE
			SYNTAX	INTEGER
			MAX-ACCESS	read-only
			STATUS	current
			::= { hmWanMbus67 91 }

hmWanMbus67VIF2B		OBJECT-TYPE
			SYNTAX	INTEGER
			MAX-ACCESS	read-only
			STATUS	current
			::= { hmWanMbus67 92 }

hmWanMbus67Value2B		OBJECT-TYPE
			SYNTAX	INTEGER
			MAX-ACCESS	read-only
			STATUS	current
			::= { hmWanMbus67 93 }

hmWanMbus67VIF2C		OBJECT-TYPE
			SYNTAX	INTEGER
			MAX-ACCESS	read-only
			STATUS	current
			::= { hmWanMbus67 94 }

hmWanMbus67Value2C		OBJECT-TYPE
			SYNTAX	INTEGER
			MAX-ACCESS	read-only
			STATUS	current
			::= { hmWanMbus67 95 }

hmWanMbus67VIF2D		OBJECT-TYPE
			SYNTAX	INTEGER
			MAX-ACCESS	read-only
			STATUS	current
			::= { hmWanMbus67 96 }

hmWanMbus67Value2D		OBJECT-TYPE
			SYNTAX	INTEGER
			MAX-ACCESS	read-only
			STATUS	current
			::= { hmWanMbus67 97 }

hmWanMbus67VIF2E		OBJECT-TYPE
			SYNTAX	INTEGER
			MAX-ACCESS	read-only
			STATUS	current
			::= { hmWanMbus67 98 }

hmWanMbus67Value2E		OBJECT-TYPE
			SYNTAX	INTEGER
			MAX-ACCESS	read-only
			STATUS	current
			::= { hmWanMbus67 99 }

hmWanMbus67VIF2F		OBJECT-TYPE
			SYNTAX	INTEGER
			MAX-ACCESS	read-only
			STATUS	current
			::= { hmWanMbus67 100 }

hmWanMbus67Value2F		OBJECT-TYPE
			SYNTAX	INTEGER
			MAX-ACCESS	read-only
			STATUS	current
			::= { hmWanMbus67 101 }

hmWanMbus68			OBJECT IDENTIFIER ::= { hmWanMbus 104 }

hmWanMbus68IdNumber		OBJECT-TYPE
			SYNTAX	Gauge32
			MAX-ACCESS	read-only
			STATUS	current
			::= { hmWanMbus68 1 }

hmWanMbus68Manufacturer	OBJECT-TYPE
			SYNTAX	Gauge32
			MAX-ACCESS	read-only
			STATUS	current
			::= { hmWanMbus68 2 }

hmWanMbus68Version		OBJECT-TYPE
			SYNTAX	Gauge32
			MAX-ACCESS	read-only
			STATUS	current
			::= { hmWanMbus68 3 }

hmWanMbus68Medium		OBJECT-TYPE
			SYNTAX	Gauge32
			MAX-ACCESS	read-only
			STATUS	current
			::= { hmWanMbus68 4 }

hmWanMbus68Status		OBJECT-TYPE
			SYNTAX	Gauge32
			MAX-ACCESS	read-only
			STATUS	current
			::= { hmWanMbus68 5 }

hmWanMbus68VIF00		OBJECT-TYPE
			SYNTAX	INTEGER
			MAX-ACCESS	read-only
			STATUS	current
			::= { hmWanMbus68 6 }

hmWanMbus68Value00		OBJECT-TYPE
			SYNTAX	INTEGER
			MAX-ACCESS	read-only
			STATUS	current
			::= { hmWanMbus68 7 }

hmWanMbus68VIF01		OBJECT-TYPE
			SYNTAX	INTEGER
			MAX-ACCESS	read-only
			STATUS	current
			::= { hmWanMbus68 8 }

hmWanMbus68Value01		OBJECT-TYPE
			SYNTAX	INTEGER
			MAX-ACCESS	read-only
			STATUS	current
			::= { hmWanMbus68 9 }

hmWanMbus68VIF02		OBJECT-TYPE
			SYNTAX	INTEGER
			MAX-ACCESS	read-only
			STATUS	current
			::= { hmWanMbus68 10 }

hmWanMbus68Value02		OBJECT-TYPE
			SYNTAX	INTEGER
			MAX-ACCESS	read-only
			STATUS	current
			::= { hmWanMbus68 11 }

hmWanMbus68VIF03		OBJECT-TYPE
			SYNTAX	INTEGER
			MAX-ACCESS	read-only
			STATUS	current
			::= { hmWanMbus68 12 }

hmWanMbus68Value03		OBJECT-TYPE
			SYNTAX	INTEGER
			MAX-ACCESS	read-only
			STATUS	current
			::= { hmWanMbus68 13 }

hmWanMbus68VIF04		OBJECT-TYPE
			SYNTAX	INTEGER
			MAX-ACCESS	read-only
			STATUS	current
			::= { hmWanMbus68 14 }

hmWanMbus68Value04		OBJECT-TYPE
			SYNTAX	INTEGER
			MAX-ACCESS	read-only
			STATUS	current
			::= { hmWanMbus68 15 }

hmWanMbus68VIF05		OBJECT-TYPE
			SYNTAX	INTEGER
			MAX-ACCESS	read-only
			STATUS	current
			::= { hmWanMbus68 16 }

hmWanMbus68Value05		OBJECT-TYPE
			SYNTAX	INTEGER
			MAX-ACCESS	read-only
			STATUS	current
			::= { hmWanMbus68 17 }

hmWanMbus68VIF06		OBJECT-TYPE
			SYNTAX	INTEGER
			MAX-ACCESS	read-only
			STATUS	current
			::= { hmWanMbus68 18 }

hmWanMbus68Value06		OBJECT-TYPE
			SYNTAX	INTEGER
			MAX-ACCESS	read-only
			STATUS	current
			::= { hmWanMbus68 19 }

hmWanMbus68VIF07		OBJECT-TYPE
			SYNTAX	INTEGER
			MAX-ACCESS	read-only
			STATUS	current
			::= { hmWanMbus68 20 }

hmWanMbus68Value07		OBJECT-TYPE
			SYNTAX	INTEGER
			MAX-ACCESS	read-only
			STATUS	current
			::= { hmWanMbus68 21 }

hmWanMbus68VIF08		OBJECT-TYPE
			SYNTAX	INTEGER
			MAX-ACCESS	read-only
			STATUS	current
			::= { hmWanMbus68 22 }

hmWanMbus68Value08		OBJECT-TYPE
			SYNTAX	INTEGER
			MAX-ACCESS	read-only
			STATUS	current
			::= { hmWanMbus68 23 }

hmWanMbus68VIF09		OBJECT-TYPE
			SYNTAX	INTEGER
			MAX-ACCESS	read-only
			STATUS	current
			::= { hmWanMbus68 24 }

hmWanMbus68Value09		OBJECT-TYPE
			SYNTAX	INTEGER
			MAX-ACCESS	read-only
			STATUS	current
			::= { hmWanMbus68 25 }

hmWanMbus68VIF0A		OBJECT-TYPE
			SYNTAX	INTEGER
			MAX-ACCESS	read-only
			STATUS	current
			::= { hmWanMbus68 26 }

hmWanMbus68Value0A		OBJECT-TYPE
			SYNTAX	INTEGER
			MAX-ACCESS	read-only
			STATUS	current
			::= { hmWanMbus68 27 }

hmWanMbus68VIF0B		OBJECT-TYPE
			SYNTAX	INTEGER
			MAX-ACCESS	read-only
			STATUS	current
			::= { hmWanMbus68 28 }

hmWanMbus68Value0B		OBJECT-TYPE
			SYNTAX	INTEGER
			MAX-ACCESS	read-only
			STATUS	current
			::= { hmWanMbus68 29 }

hmWanMbus68VIF0C		OBJECT-TYPE
			SYNTAX	INTEGER
			MAX-ACCESS	read-only
			STATUS	current
			::= { hmWanMbus68 30 }

hmWanMbus68Value0C		OBJECT-TYPE
			SYNTAX	INTEGER
			MAX-ACCESS	read-only
			STATUS	current
			::= { hmWanMbus68 31 }

hmWanMbus68VIF0D		OBJECT-TYPE
			SYNTAX	INTEGER
			MAX-ACCESS	read-only
			STATUS	current
			::= { hmWanMbus68 32 }

hmWanMbus68Value0D		OBJECT-TYPE
			SYNTAX	INTEGER
			MAX-ACCESS	read-only
			STATUS	current
			::= { hmWanMbus68 33 }

hmWanMbus68VIF0E		OBJECT-TYPE
			SYNTAX	INTEGER
			MAX-ACCESS	read-only
			STATUS	current
			::= { hmWanMbus68 34 }

hmWanMbus68Value0E		OBJECT-TYPE
			SYNTAX	INTEGER
			MAX-ACCESS	read-only
			STATUS	current
			::= { hmWanMbus68 35 }

hmWanMbus68VIF0F		OBJECT-TYPE
			SYNTAX	INTEGER
			MAX-ACCESS	read-only
			STATUS	current
			::= { hmWanMbus68 36 }

hmWanMbus68Value0F		OBJECT-TYPE
			SYNTAX	INTEGER
			MAX-ACCESS	read-only
			STATUS	current
			::= { hmWanMbus68 37 }

hmWanMbus68VIF10		OBJECT-TYPE
			SYNTAX	INTEGER
			MAX-ACCESS	read-only
			STATUS	current
			::= { hmWanMbus68 38 }

hmWanMbus68Value10		OBJECT-TYPE
			SYNTAX	INTEGER
			MAX-ACCESS	read-only
			STATUS	current
			::= { hmWanMbus68 39 }

hmWanMbus68VIF11		OBJECT-TYPE
			SYNTAX	INTEGER
			MAX-ACCESS	read-only
			STATUS	current
			::= { hmWanMbus68 40 }

hmWanMbus68Value11		OBJECT-TYPE
			SYNTAX	INTEGER
			MAX-ACCESS	read-only
			STATUS	current
			::= { hmWanMbus68 41 }

hmWanMbus68VIF12		OBJECT-TYPE
			SYNTAX	INTEGER
			MAX-ACCESS	read-only
			STATUS	current
			::= { hmWanMbus68 42 }

hmWanMbus68Value12		OBJECT-TYPE
			SYNTAX	INTEGER
			MAX-ACCESS	read-only
			STATUS	current
			::= { hmWanMbus68 43 }

hmWanMbus68VIF13		OBJECT-TYPE
			SYNTAX	INTEGER
			MAX-ACCESS	read-only
			STATUS	current
			::= { hmWanMbus68 44 }

hmWanMbus68Value13		OBJECT-TYPE
			SYNTAX	INTEGER
			MAX-ACCESS	read-only
			STATUS	current
			::= { hmWanMbus68 45 }

hmWanMbus68VIF14		OBJECT-TYPE
			SYNTAX	INTEGER
			MAX-ACCESS	read-only
			STATUS	current
			::= { hmWanMbus68 46 }

hmWanMbus68Value14		OBJECT-TYPE
			SYNTAX	INTEGER
			MAX-ACCESS	read-only
			STATUS	current
			::= { hmWanMbus68 47 }

hmWanMbus68VIF15		OBJECT-TYPE
			SYNTAX	INTEGER
			MAX-ACCESS	read-only
			STATUS	current
			::= { hmWanMbus68 48 }

hmWanMbus68Value15		OBJECT-TYPE
			SYNTAX	INTEGER
			MAX-ACCESS	read-only
			STATUS	current
			::= { hmWanMbus68 49 }

hmWanMbus68VIF16		OBJECT-TYPE
			SYNTAX	INTEGER
			MAX-ACCESS	read-only
			STATUS	current
			::= { hmWanMbus68 50 }

hmWanMbus68Value16		OBJECT-TYPE
			SYNTAX	INTEGER
			MAX-ACCESS	read-only
			STATUS	current
			::= { hmWanMbus68 51 }

hmWanMbus68VIF17		OBJECT-TYPE
			SYNTAX	INTEGER
			MAX-ACCESS	read-only
			STATUS	current
			::= { hmWanMbus68 52 }

hmWanMbus68Value17		OBJECT-TYPE
			SYNTAX	INTEGER
			MAX-ACCESS	read-only
			STATUS	current
			::= { hmWanMbus68 53 }

hmWanMbus68VIF18		OBJECT-TYPE
			SYNTAX	INTEGER
			MAX-ACCESS	read-only
			STATUS	current
			::= { hmWanMbus68 54 }

hmWanMbus68Value18		OBJECT-TYPE
			SYNTAX	INTEGER
			MAX-ACCESS	read-only
			STATUS	current
			::= { hmWanMbus68 55 }

hmWanMbus68VIF19		OBJECT-TYPE
			SYNTAX	INTEGER
			MAX-ACCESS	read-only
			STATUS	current
			::= { hmWanMbus68 56 }

hmWanMbus68Value19		OBJECT-TYPE
			SYNTAX	INTEGER
			MAX-ACCESS	read-only
			STATUS	current
			::= { hmWanMbus68 57 }

hmWanMbus68VIF1A		OBJECT-TYPE
			SYNTAX	INTEGER
			MAX-ACCESS	read-only
			STATUS	current
			::= { hmWanMbus68 58 }

hmWanMbus68Value1A		OBJECT-TYPE
			SYNTAX	INTEGER
			MAX-ACCESS	read-only
			STATUS	current
			::= { hmWanMbus68 59 }

hmWanMbus68VIF1B		OBJECT-TYPE
			SYNTAX	INTEGER
			MAX-ACCESS	read-only
			STATUS	current
			::= { hmWanMbus68 60 }

hmWanMbus68Value1B		OBJECT-TYPE
			SYNTAX	INTEGER
			MAX-ACCESS	read-only
			STATUS	current
			::= { hmWanMbus68 61 }

hmWanMbus68VIF1C		OBJECT-TYPE
			SYNTAX	INTEGER
			MAX-ACCESS	read-only
			STATUS	current
			::= { hmWanMbus68 62 }

hmWanMbus68Value1C		OBJECT-TYPE
			SYNTAX	INTEGER
			MAX-ACCESS	read-only
			STATUS	current
			::= { hmWanMbus68 63 }

hmWanMbus68VIF1D		OBJECT-TYPE
			SYNTAX	INTEGER
			MAX-ACCESS	read-only
			STATUS	current
			::= { hmWanMbus68 64 }

hmWanMbus68Value1D		OBJECT-TYPE
			SYNTAX	INTEGER
			MAX-ACCESS	read-only
			STATUS	current
			::= { hmWanMbus68 65 }

hmWanMbus68VIF1E		OBJECT-TYPE
			SYNTAX	INTEGER
			MAX-ACCESS	read-only
			STATUS	current
			::= { hmWanMbus68 66 }

hmWanMbus68Value1E		OBJECT-TYPE
			SYNTAX	INTEGER
			MAX-ACCESS	read-only
			STATUS	current
			::= { hmWanMbus68 67 }

hmWanMbus68VIF1F		OBJECT-TYPE
			SYNTAX	INTEGER
			MAX-ACCESS	read-only
			STATUS	current
			::= { hmWanMbus68 68 }

hmWanMbus68Value1F		OBJECT-TYPE
			SYNTAX	INTEGER
			MAX-ACCESS	read-only
			STATUS	current
			::= { hmWanMbus68 69 }

hmWanMbus68VIF20		OBJECT-TYPE
			SYNTAX	INTEGER
			MAX-ACCESS	read-only
			STATUS	current
			::= { hmWanMbus68 70 }

hmWanMbus68Value20		OBJECT-TYPE
			SYNTAX	INTEGER
			MAX-ACCESS	read-only
			STATUS	current
			::= { hmWanMbus68 71 }

hmWanMbus68VIF21		OBJECT-TYPE
			SYNTAX	INTEGER
			MAX-ACCESS	read-only
			STATUS	current
			::= { hmWanMbus68 72 }

hmWanMbus68Value21		OBJECT-TYPE
			SYNTAX	INTEGER
			MAX-ACCESS	read-only
			STATUS	current
			::= { hmWanMbus68 73 }

hmWanMbus68VIF22		OBJECT-TYPE
			SYNTAX	INTEGER
			MAX-ACCESS	read-only
			STATUS	current
			::= { hmWanMbus68 74 }

hmWanMbus68Value22		OBJECT-TYPE
			SYNTAX	INTEGER
			MAX-ACCESS	read-only
			STATUS	current
			::= { hmWanMbus68 75 }

hmWanMbus68VIF23		OBJECT-TYPE
			SYNTAX	INTEGER
			MAX-ACCESS	read-only
			STATUS	current
			::= { hmWanMbus68 76 }

hmWanMbus68Value23		OBJECT-TYPE
			SYNTAX	INTEGER
			MAX-ACCESS	read-only
			STATUS	current
			::= { hmWanMbus68 77 }

hmWanMbus68VIF24		OBJECT-TYPE
			SYNTAX	INTEGER
			MAX-ACCESS	read-only
			STATUS	current
			::= { hmWanMbus68 78 }

hmWanMbus68Value24		OBJECT-TYPE
			SYNTAX	INTEGER
			MAX-ACCESS	read-only
			STATUS	current
			::= { hmWanMbus68 79 }

hmWanMbus68VIF25		OBJECT-TYPE
			SYNTAX	INTEGER
			MAX-ACCESS	read-only
			STATUS	current
			::= { hmWanMbus68 80 }

hmWanMbus68Value25		OBJECT-TYPE
			SYNTAX	INTEGER
			MAX-ACCESS	read-only
			STATUS	current
			::= { hmWanMbus68 81 }

hmWanMbus68VIF26		OBJECT-TYPE
			SYNTAX	INTEGER
			MAX-ACCESS	read-only
			STATUS	current
			::= { hmWanMbus68 82 }

hmWanMbus68Value26		OBJECT-TYPE
			SYNTAX	INTEGER
			MAX-ACCESS	read-only
			STATUS	current
			::= { hmWanMbus68 83 }

hmWanMbus68VIF27		OBJECT-TYPE
			SYNTAX	INTEGER
			MAX-ACCESS	read-only
			STATUS	current
			::= { hmWanMbus68 84 }

hmWanMbus68Value27		OBJECT-TYPE
			SYNTAX	INTEGER
			MAX-ACCESS	read-only
			STATUS	current
			::= { hmWanMbus68 85 }

hmWanMbus68VIF28		OBJECT-TYPE
			SYNTAX	INTEGER
			MAX-ACCESS	read-only
			STATUS	current
			::= { hmWanMbus68 86 }

hmWanMbus68Value28		OBJECT-TYPE
			SYNTAX	INTEGER
			MAX-ACCESS	read-only
			STATUS	current
			::= { hmWanMbus68 87 }

hmWanMbus68VIF29		OBJECT-TYPE
			SYNTAX	INTEGER
			MAX-ACCESS	read-only
			STATUS	current
			::= { hmWanMbus68 88 }

hmWanMbus68Value29		OBJECT-TYPE
			SYNTAX	INTEGER
			MAX-ACCESS	read-only
			STATUS	current
			::= { hmWanMbus68 89 }

hmWanMbus68VIF2A		OBJECT-TYPE
			SYNTAX	INTEGER
			MAX-ACCESS	read-only
			STATUS	current
			::= { hmWanMbus68 90 }

hmWanMbus68Value2A		OBJECT-TYPE
			SYNTAX	INTEGER
			MAX-ACCESS	read-only
			STATUS	current
			::= { hmWanMbus68 91 }

hmWanMbus68VIF2B		OBJECT-TYPE
			SYNTAX	INTEGER
			MAX-ACCESS	read-only
			STATUS	current
			::= { hmWanMbus68 92 }

hmWanMbus68Value2B		OBJECT-TYPE
			SYNTAX	INTEGER
			MAX-ACCESS	read-only
			STATUS	current
			::= { hmWanMbus68 93 }

hmWanMbus68VIF2C		OBJECT-TYPE
			SYNTAX	INTEGER
			MAX-ACCESS	read-only
			STATUS	current
			::= { hmWanMbus68 94 }

hmWanMbus68Value2C		OBJECT-TYPE
			SYNTAX	INTEGER
			MAX-ACCESS	read-only
			STATUS	current
			::= { hmWanMbus68 95 }

hmWanMbus68VIF2D		OBJECT-TYPE
			SYNTAX	INTEGER
			MAX-ACCESS	read-only
			STATUS	current
			::= { hmWanMbus68 96 }

hmWanMbus68Value2D		OBJECT-TYPE
			SYNTAX	INTEGER
			MAX-ACCESS	read-only
			STATUS	current
			::= { hmWanMbus68 97 }

hmWanMbus68VIF2E		OBJECT-TYPE
			SYNTAX	INTEGER
			MAX-ACCESS	read-only
			STATUS	current
			::= { hmWanMbus68 98 }

hmWanMbus68Value2E		OBJECT-TYPE
			SYNTAX	INTEGER
			MAX-ACCESS	read-only
			STATUS	current
			::= { hmWanMbus68 99 }

hmWanMbus68VIF2F		OBJECT-TYPE
			SYNTAX	INTEGER
			MAX-ACCESS	read-only
			STATUS	current
			::= { hmWanMbus68 100 }

hmWanMbus68Value2F		OBJECT-TYPE
			SYNTAX	INTEGER
			MAX-ACCESS	read-only
			STATUS	current
			::= { hmWanMbus68 101 }

hmWanMbus69			OBJECT IDENTIFIER ::= { hmWanMbus 105 }

hmWanMbus69IdNumber		OBJECT-TYPE
			SYNTAX	Gauge32
			MAX-ACCESS	read-only
			STATUS	current
			::= { hmWanMbus69 1 }

hmWanMbus69Manufacturer	OBJECT-TYPE
			SYNTAX	Gauge32
			MAX-ACCESS	read-only
			STATUS	current
			::= { hmWanMbus69 2 }

hmWanMbus69Version		OBJECT-TYPE
			SYNTAX	Gauge32
			MAX-ACCESS	read-only
			STATUS	current
			::= { hmWanMbus69 3 }

hmWanMbus69Medium		OBJECT-TYPE
			SYNTAX	Gauge32
			MAX-ACCESS	read-only
			STATUS	current
			::= { hmWanMbus69 4 }

hmWanMbus69Status		OBJECT-TYPE
			SYNTAX	Gauge32
			MAX-ACCESS	read-only
			STATUS	current
			::= { hmWanMbus69 5 }

hmWanMbus69VIF00		OBJECT-TYPE
			SYNTAX	INTEGER
			MAX-ACCESS	read-only
			STATUS	current
			::= { hmWanMbus69 6 }

hmWanMbus69Value00		OBJECT-TYPE
			SYNTAX	INTEGER
			MAX-ACCESS	read-only
			STATUS	current
			::= { hmWanMbus69 7 }

hmWanMbus69VIF01		OBJECT-TYPE
			SYNTAX	INTEGER
			MAX-ACCESS	read-only
			STATUS	current
			::= { hmWanMbus69 8 }

hmWanMbus69Value01		OBJECT-TYPE
			SYNTAX	INTEGER
			MAX-ACCESS	read-only
			STATUS	current
			::= { hmWanMbus69 9 }

hmWanMbus69VIF02		OBJECT-TYPE
			SYNTAX	INTEGER
			MAX-ACCESS	read-only
			STATUS	current
			::= { hmWanMbus69 10 }

hmWanMbus69Value02		OBJECT-TYPE
			SYNTAX	INTEGER
			MAX-ACCESS	read-only
			STATUS	current
			::= { hmWanMbus69 11 }

hmWanMbus69VIF03		OBJECT-TYPE
			SYNTAX	INTEGER
			MAX-ACCESS	read-only
			STATUS	current
			::= { hmWanMbus69 12 }

hmWanMbus69Value03		OBJECT-TYPE
			SYNTAX	INTEGER
			MAX-ACCESS	read-only
			STATUS	current
			::= { hmWanMbus69 13 }

hmWanMbus69VIF04		OBJECT-TYPE
			SYNTAX	INTEGER
			MAX-ACCESS	read-only
			STATUS	current
			::= { hmWanMbus69 14 }

hmWanMbus69Value04		OBJECT-TYPE
			SYNTAX	INTEGER
			MAX-ACCESS	read-only
			STATUS	current
			::= { hmWanMbus69 15 }

hmWanMbus69VIF05		OBJECT-TYPE
			SYNTAX	INTEGER
			MAX-ACCESS	read-only
			STATUS	current
			::= { hmWanMbus69 16 }

hmWanMbus69Value05		OBJECT-TYPE
			SYNTAX	INTEGER
			MAX-ACCESS	read-only
			STATUS	current
			::= { hmWanMbus69 17 }

hmWanMbus69VIF06		OBJECT-TYPE
			SYNTAX	INTEGER
			MAX-ACCESS	read-only
			STATUS	current
			::= { hmWanMbus69 18 }

hmWanMbus69Value06		OBJECT-TYPE
			SYNTAX	INTEGER
			MAX-ACCESS	read-only
			STATUS	current
			::= { hmWanMbus69 19 }

hmWanMbus69VIF07		OBJECT-TYPE
			SYNTAX	INTEGER
			MAX-ACCESS	read-only
			STATUS	current
			::= { hmWanMbus69 20 }

hmWanMbus69Value07		OBJECT-TYPE
			SYNTAX	INTEGER
			MAX-ACCESS	read-only
			STATUS	current
			::= { hmWanMbus69 21 }

hmWanMbus69VIF08		OBJECT-TYPE
			SYNTAX	INTEGER
			MAX-ACCESS	read-only
			STATUS	current
			::= { hmWanMbus69 22 }

hmWanMbus69Value08		OBJECT-TYPE
			SYNTAX	INTEGER
			MAX-ACCESS	read-only
			STATUS	current
			::= { hmWanMbus69 23 }

hmWanMbus69VIF09		OBJECT-TYPE
			SYNTAX	INTEGER
			MAX-ACCESS	read-only
			STATUS	current
			::= { hmWanMbus69 24 }

hmWanMbus69Value09		OBJECT-TYPE
			SYNTAX	INTEGER
			MAX-ACCESS	read-only
			STATUS	current
			::= { hmWanMbus69 25 }

hmWanMbus69VIF0A		OBJECT-TYPE
			SYNTAX	INTEGER
			MAX-ACCESS	read-only
			STATUS	current
			::= { hmWanMbus69 26 }

hmWanMbus69Value0A		OBJECT-TYPE
			SYNTAX	INTEGER
			MAX-ACCESS	read-only
			STATUS	current
			::= { hmWanMbus69 27 }

hmWanMbus69VIF0B		OBJECT-TYPE
			SYNTAX	INTEGER
			MAX-ACCESS	read-only
			STATUS	current
			::= { hmWanMbus69 28 }

hmWanMbus69Value0B		OBJECT-TYPE
			SYNTAX	INTEGER
			MAX-ACCESS	read-only
			STATUS	current
			::= { hmWanMbus69 29 }

hmWanMbus69VIF0C		OBJECT-TYPE
			SYNTAX	INTEGER
			MAX-ACCESS	read-only
			STATUS	current
			::= { hmWanMbus69 30 }

hmWanMbus69Value0C		OBJECT-TYPE
			SYNTAX	INTEGER
			MAX-ACCESS	read-only
			STATUS	current
			::= { hmWanMbus69 31 }

hmWanMbus69VIF0D		OBJECT-TYPE
			SYNTAX	INTEGER
			MAX-ACCESS	read-only
			STATUS	current
			::= { hmWanMbus69 32 }

hmWanMbus69Value0D		OBJECT-TYPE
			SYNTAX	INTEGER
			MAX-ACCESS	read-only
			STATUS	current
			::= { hmWanMbus69 33 }

hmWanMbus69VIF0E		OBJECT-TYPE
			SYNTAX	INTEGER
			MAX-ACCESS	read-only
			STATUS	current
			::= { hmWanMbus69 34 }

hmWanMbus69Value0E		OBJECT-TYPE
			SYNTAX	INTEGER
			MAX-ACCESS	read-only
			STATUS	current
			::= { hmWanMbus69 35 }

hmWanMbus69VIF0F		OBJECT-TYPE
			SYNTAX	INTEGER
			MAX-ACCESS	read-only
			STATUS	current
			::= { hmWanMbus69 36 }

hmWanMbus69Value0F		OBJECT-TYPE
			SYNTAX	INTEGER
			MAX-ACCESS	read-only
			STATUS	current
			::= { hmWanMbus69 37 }

hmWanMbus69VIF10		OBJECT-TYPE
			SYNTAX	INTEGER
			MAX-ACCESS	read-only
			STATUS	current
			::= { hmWanMbus69 38 }

hmWanMbus69Value10		OBJECT-TYPE
			SYNTAX	INTEGER
			MAX-ACCESS	read-only
			STATUS	current
			::= { hmWanMbus69 39 }

hmWanMbus69VIF11		OBJECT-TYPE
			SYNTAX	INTEGER
			MAX-ACCESS	read-only
			STATUS	current
			::= { hmWanMbus69 40 }

hmWanMbus69Value11		OBJECT-TYPE
			SYNTAX	INTEGER
			MAX-ACCESS	read-only
			STATUS	current
			::= { hmWanMbus69 41 }

hmWanMbus69VIF12		OBJECT-TYPE
			SYNTAX	INTEGER
			MAX-ACCESS	read-only
			STATUS	current
			::= { hmWanMbus69 42 }

hmWanMbus69Value12		OBJECT-TYPE
			SYNTAX	INTEGER
			MAX-ACCESS	read-only
			STATUS	current
			::= { hmWanMbus69 43 }

hmWanMbus69VIF13		OBJECT-TYPE
			SYNTAX	INTEGER
			MAX-ACCESS	read-only
			STATUS	current
			::= { hmWanMbus69 44 }

hmWanMbus69Value13		OBJECT-TYPE
			SYNTAX	INTEGER
			MAX-ACCESS	read-only
			STATUS	current
			::= { hmWanMbus69 45 }

hmWanMbus69VIF14		OBJECT-TYPE
			SYNTAX	INTEGER
			MAX-ACCESS	read-only
			STATUS	current
			::= { hmWanMbus69 46 }

hmWanMbus69Value14		OBJECT-TYPE
			SYNTAX	INTEGER
			MAX-ACCESS	read-only
			STATUS	current
			::= { hmWanMbus69 47 }

hmWanMbus69VIF15		OBJECT-TYPE
			SYNTAX	INTEGER
			MAX-ACCESS	read-only
			STATUS	current
			::= { hmWanMbus69 48 }

hmWanMbus69Value15		OBJECT-TYPE
			SYNTAX	INTEGER
			MAX-ACCESS	read-only
			STATUS	current
			::= { hmWanMbus69 49 }

hmWanMbus69VIF16		OBJECT-TYPE
			SYNTAX	INTEGER
			MAX-ACCESS	read-only
			STATUS	current
			::= { hmWanMbus69 50 }

hmWanMbus69Value16		OBJECT-TYPE
			SYNTAX	INTEGER
			MAX-ACCESS	read-only
			STATUS	current
			::= { hmWanMbus69 51 }

hmWanMbus69VIF17		OBJECT-TYPE
			SYNTAX	INTEGER
			MAX-ACCESS	read-only
			STATUS	current
			::= { hmWanMbus69 52 }

hmWanMbus69Value17		OBJECT-TYPE
			SYNTAX	INTEGER
			MAX-ACCESS	read-only
			STATUS	current
			::= { hmWanMbus69 53 }

hmWanMbus69VIF18		OBJECT-TYPE
			SYNTAX	INTEGER
			MAX-ACCESS	read-only
			STATUS	current
			::= { hmWanMbus69 54 }

hmWanMbus69Value18		OBJECT-TYPE
			SYNTAX	INTEGER
			MAX-ACCESS	read-only
			STATUS	current
			::= { hmWanMbus69 55 }

hmWanMbus69VIF19		OBJECT-TYPE
			SYNTAX	INTEGER
			MAX-ACCESS	read-only
			STATUS	current
			::= { hmWanMbus69 56 }

hmWanMbus69Value19		OBJECT-TYPE
			SYNTAX	INTEGER
			MAX-ACCESS	read-only
			STATUS	current
			::= { hmWanMbus69 57 }

hmWanMbus69VIF1A		OBJECT-TYPE
			SYNTAX	INTEGER
			MAX-ACCESS	read-only
			STATUS	current
			::= { hmWanMbus69 58 }

hmWanMbus69Value1A		OBJECT-TYPE
			SYNTAX	INTEGER
			MAX-ACCESS	read-only
			STATUS	current
			::= { hmWanMbus69 59 }

hmWanMbus69VIF1B		OBJECT-TYPE
			SYNTAX	INTEGER
			MAX-ACCESS	read-only
			STATUS	current
			::= { hmWanMbus69 60 }

hmWanMbus69Value1B		OBJECT-TYPE
			SYNTAX	INTEGER
			MAX-ACCESS	read-only
			STATUS	current
			::= { hmWanMbus69 61 }

hmWanMbus69VIF1C		OBJECT-TYPE
			SYNTAX	INTEGER
			MAX-ACCESS	read-only
			STATUS	current
			::= { hmWanMbus69 62 }

hmWanMbus69Value1C		OBJECT-TYPE
			SYNTAX	INTEGER
			MAX-ACCESS	read-only
			STATUS	current
			::= { hmWanMbus69 63 }

hmWanMbus69VIF1D		OBJECT-TYPE
			SYNTAX	INTEGER
			MAX-ACCESS	read-only
			STATUS	current
			::= { hmWanMbus69 64 }

hmWanMbus69Value1D		OBJECT-TYPE
			SYNTAX	INTEGER
			MAX-ACCESS	read-only
			STATUS	current
			::= { hmWanMbus69 65 }

hmWanMbus69VIF1E		OBJECT-TYPE
			SYNTAX	INTEGER
			MAX-ACCESS	read-only
			STATUS	current
			::= { hmWanMbus69 66 }

hmWanMbus69Value1E		OBJECT-TYPE
			SYNTAX	INTEGER
			MAX-ACCESS	read-only
			STATUS	current
			::= { hmWanMbus69 67 }

hmWanMbus69VIF1F		OBJECT-TYPE
			SYNTAX	INTEGER
			MAX-ACCESS	read-only
			STATUS	current
			::= { hmWanMbus69 68 }

hmWanMbus69Value1F		OBJECT-TYPE
			SYNTAX	INTEGER
			MAX-ACCESS	read-only
			STATUS	current
			::= { hmWanMbus69 69 }

hmWanMbus69VIF20		OBJECT-TYPE
			SYNTAX	INTEGER
			MAX-ACCESS	read-only
			STATUS	current
			::= { hmWanMbus69 70 }

hmWanMbus69Value20		OBJECT-TYPE
			SYNTAX	INTEGER
			MAX-ACCESS	read-only
			STATUS	current
			::= { hmWanMbus69 71 }

hmWanMbus69VIF21		OBJECT-TYPE
			SYNTAX	INTEGER
			MAX-ACCESS	read-only
			STATUS	current
			::= { hmWanMbus69 72 }

hmWanMbus69Value21		OBJECT-TYPE
			SYNTAX	INTEGER
			MAX-ACCESS	read-only
			STATUS	current
			::= { hmWanMbus69 73 }

hmWanMbus69VIF22		OBJECT-TYPE
			SYNTAX	INTEGER
			MAX-ACCESS	read-only
			STATUS	current
			::= { hmWanMbus69 74 }

hmWanMbus69Value22		OBJECT-TYPE
			SYNTAX	INTEGER
			MAX-ACCESS	read-only
			STATUS	current
			::= { hmWanMbus69 75 }

hmWanMbus69VIF23		OBJECT-TYPE
			SYNTAX	INTEGER
			MAX-ACCESS	read-only
			STATUS	current
			::= { hmWanMbus69 76 }

hmWanMbus69Value23		OBJECT-TYPE
			SYNTAX	INTEGER
			MAX-ACCESS	read-only
			STATUS	current
			::= { hmWanMbus69 77 }

hmWanMbus69VIF24		OBJECT-TYPE
			SYNTAX	INTEGER
			MAX-ACCESS	read-only
			STATUS	current
			::= { hmWanMbus69 78 }

hmWanMbus69Value24		OBJECT-TYPE
			SYNTAX	INTEGER
			MAX-ACCESS	read-only
			STATUS	current
			::= { hmWanMbus69 79 }

hmWanMbus69VIF25		OBJECT-TYPE
			SYNTAX	INTEGER
			MAX-ACCESS	read-only
			STATUS	current
			::= { hmWanMbus69 80 }

hmWanMbus69Value25		OBJECT-TYPE
			SYNTAX	INTEGER
			MAX-ACCESS	read-only
			STATUS	current
			::= { hmWanMbus69 81 }

hmWanMbus69VIF26		OBJECT-TYPE
			SYNTAX	INTEGER
			MAX-ACCESS	read-only
			STATUS	current
			::= { hmWanMbus69 82 }

hmWanMbus69Value26		OBJECT-TYPE
			SYNTAX	INTEGER
			MAX-ACCESS	read-only
			STATUS	current
			::= { hmWanMbus69 83 }

hmWanMbus69VIF27		OBJECT-TYPE
			SYNTAX	INTEGER
			MAX-ACCESS	read-only
			STATUS	current
			::= { hmWanMbus69 84 }

hmWanMbus69Value27		OBJECT-TYPE
			SYNTAX	INTEGER
			MAX-ACCESS	read-only
			STATUS	current
			::= { hmWanMbus69 85 }

hmWanMbus69VIF28		OBJECT-TYPE
			SYNTAX	INTEGER
			MAX-ACCESS	read-only
			STATUS	current
			::= { hmWanMbus69 86 }

hmWanMbus69Value28		OBJECT-TYPE
			SYNTAX	INTEGER
			MAX-ACCESS	read-only
			STATUS	current
			::= { hmWanMbus69 87 }

hmWanMbus69VIF29		OBJECT-TYPE
			SYNTAX	INTEGER
			MAX-ACCESS	read-only
			STATUS	current
			::= { hmWanMbus69 88 }

hmWanMbus69Value29		OBJECT-TYPE
			SYNTAX	INTEGER
			MAX-ACCESS	read-only
			STATUS	current
			::= { hmWanMbus69 89 }

hmWanMbus69VIF2A		OBJECT-TYPE
			SYNTAX	INTEGER
			MAX-ACCESS	read-only
			STATUS	current
			::= { hmWanMbus69 90 }

hmWanMbus69Value2A		OBJECT-TYPE
			SYNTAX	INTEGER
			MAX-ACCESS	read-only
			STATUS	current
			::= { hmWanMbus69 91 }

hmWanMbus69VIF2B		OBJECT-TYPE
			SYNTAX	INTEGER
			MAX-ACCESS	read-only
			STATUS	current
			::= { hmWanMbus69 92 }

hmWanMbus69Value2B		OBJECT-TYPE
			SYNTAX	INTEGER
			MAX-ACCESS	read-only
			STATUS	current
			::= { hmWanMbus69 93 }

hmWanMbus69VIF2C		OBJECT-TYPE
			SYNTAX	INTEGER
			MAX-ACCESS	read-only
			STATUS	current
			::= { hmWanMbus69 94 }

hmWanMbus69Value2C		OBJECT-TYPE
			SYNTAX	INTEGER
			MAX-ACCESS	read-only
			STATUS	current
			::= { hmWanMbus69 95 }

hmWanMbus69VIF2D		OBJECT-TYPE
			SYNTAX	INTEGER
			MAX-ACCESS	read-only
			STATUS	current
			::= { hmWanMbus69 96 }

hmWanMbus69Value2D		OBJECT-TYPE
			SYNTAX	INTEGER
			MAX-ACCESS	read-only
			STATUS	current
			::= { hmWanMbus69 97 }

hmWanMbus69VIF2E		OBJECT-TYPE
			SYNTAX	INTEGER
			MAX-ACCESS	read-only
			STATUS	current
			::= { hmWanMbus69 98 }

hmWanMbus69Value2E		OBJECT-TYPE
			SYNTAX	INTEGER
			MAX-ACCESS	read-only
			STATUS	current
			::= { hmWanMbus69 99 }

hmWanMbus69VIF2F		OBJECT-TYPE
			SYNTAX	INTEGER
			MAX-ACCESS	read-only
			STATUS	current
			::= { hmWanMbus69 100 }

hmWanMbus69Value2F		OBJECT-TYPE
			SYNTAX	INTEGER
			MAX-ACCESS	read-only
			STATUS	current
			::= { hmWanMbus69 101 }

hmWanMbus6A			OBJECT IDENTIFIER ::= { hmWanMbus 106 }

hmWanMbus6AIdNumber		OBJECT-TYPE
			SYNTAX	Gauge32
			MAX-ACCESS	read-only
			STATUS	current
			::= { hmWanMbus6A 1 }

hmWanMbus6AManufacturer	OBJECT-TYPE
			SYNTAX	Gauge32
			MAX-ACCESS	read-only
			STATUS	current
			::= { hmWanMbus6A 2 }

hmWanMbus6AVersion		OBJECT-TYPE
			SYNTAX	Gauge32
			MAX-ACCESS	read-only
			STATUS	current
			::= { hmWanMbus6A 3 }

hmWanMbus6AMedium		OBJECT-TYPE
			SYNTAX	Gauge32
			MAX-ACCESS	read-only
			STATUS	current
			::= { hmWanMbus6A 4 }

hmWanMbus6AStatus		OBJECT-TYPE
			SYNTAX	Gauge32
			MAX-ACCESS	read-only
			STATUS	current
			::= { hmWanMbus6A 5 }

hmWanMbus6AVIF00		OBJECT-TYPE
			SYNTAX	INTEGER
			MAX-ACCESS	read-only
			STATUS	current
			::= { hmWanMbus6A 6 }

hmWanMbus6AValue00		OBJECT-TYPE
			SYNTAX	INTEGER
			MAX-ACCESS	read-only
			STATUS	current
			::= { hmWanMbus6A 7 }

hmWanMbus6AVIF01		OBJECT-TYPE
			SYNTAX	INTEGER
			MAX-ACCESS	read-only
			STATUS	current
			::= { hmWanMbus6A 8 }

hmWanMbus6AValue01		OBJECT-TYPE
			SYNTAX	INTEGER
			MAX-ACCESS	read-only
			STATUS	current
			::= { hmWanMbus6A 9 }

hmWanMbus6AVIF02		OBJECT-TYPE
			SYNTAX	INTEGER
			MAX-ACCESS	read-only
			STATUS	current
			::= { hmWanMbus6A 10 }

hmWanMbus6AValue02		OBJECT-TYPE
			SYNTAX	INTEGER
			MAX-ACCESS	read-only
			STATUS	current
			::= { hmWanMbus6A 11 }

hmWanMbus6AVIF03		OBJECT-TYPE
			SYNTAX	INTEGER
			MAX-ACCESS	read-only
			STATUS	current
			::= { hmWanMbus6A 12 }

hmWanMbus6AValue03		OBJECT-TYPE
			SYNTAX	INTEGER
			MAX-ACCESS	read-only
			STATUS	current
			::= { hmWanMbus6A 13 }

hmWanMbus6AVIF04		OBJECT-TYPE
			SYNTAX	INTEGER
			MAX-ACCESS	read-only
			STATUS	current
			::= { hmWanMbus6A 14 }

hmWanMbus6AValue04		OBJECT-TYPE
			SYNTAX	INTEGER
			MAX-ACCESS	read-only
			STATUS	current
			::= { hmWanMbus6A 15 }

hmWanMbus6AVIF05		OBJECT-TYPE
			SYNTAX	INTEGER
			MAX-ACCESS	read-only
			STATUS	current
			::= { hmWanMbus6A 16 }

hmWanMbus6AValue05		OBJECT-TYPE
			SYNTAX	INTEGER
			MAX-ACCESS	read-only
			STATUS	current
			::= { hmWanMbus6A 17 }

hmWanMbus6AVIF06		OBJECT-TYPE
			SYNTAX	INTEGER
			MAX-ACCESS	read-only
			STATUS	current
			::= { hmWanMbus6A 18 }

hmWanMbus6AValue06		OBJECT-TYPE
			SYNTAX	INTEGER
			MAX-ACCESS	read-only
			STATUS	current
			::= { hmWanMbus6A 19 }

hmWanMbus6AVIF07		OBJECT-TYPE
			SYNTAX	INTEGER
			MAX-ACCESS	read-only
			STATUS	current
			::= { hmWanMbus6A 20 }

hmWanMbus6AValue07		OBJECT-TYPE
			SYNTAX	INTEGER
			MAX-ACCESS	read-only
			STATUS	current
			::= { hmWanMbus6A 21 }

hmWanMbus6AVIF08		OBJECT-TYPE
			SYNTAX	INTEGER
			MAX-ACCESS	read-only
			STATUS	current
			::= { hmWanMbus6A 22 }

hmWanMbus6AValue08		OBJECT-TYPE
			SYNTAX	INTEGER
			MAX-ACCESS	read-only
			STATUS	current
			::= { hmWanMbus6A 23 }

hmWanMbus6AVIF09		OBJECT-TYPE
			SYNTAX	INTEGER
			MAX-ACCESS	read-only
			STATUS	current
			::= { hmWanMbus6A 24 }

hmWanMbus6AValue09		OBJECT-TYPE
			SYNTAX	INTEGER
			MAX-ACCESS	read-only
			STATUS	current
			::= { hmWanMbus6A 25 }

hmWanMbus6AVIF0A		OBJECT-TYPE
			SYNTAX	INTEGER
			MAX-ACCESS	read-only
			STATUS	current
			::= { hmWanMbus6A 26 }

hmWanMbus6AValue0A		OBJECT-TYPE
			SYNTAX	INTEGER
			MAX-ACCESS	read-only
			STATUS	current
			::= { hmWanMbus6A 27 }

hmWanMbus6AVIF0B		OBJECT-TYPE
			SYNTAX	INTEGER
			MAX-ACCESS	read-only
			STATUS	current
			::= { hmWanMbus6A 28 }

hmWanMbus6AValue0B		OBJECT-TYPE
			SYNTAX	INTEGER
			MAX-ACCESS	read-only
			STATUS	current
			::= { hmWanMbus6A 29 }

hmWanMbus6AVIF0C		OBJECT-TYPE
			SYNTAX	INTEGER
			MAX-ACCESS	read-only
			STATUS	current
			::= { hmWanMbus6A 30 }

hmWanMbus6AValue0C		OBJECT-TYPE
			SYNTAX	INTEGER
			MAX-ACCESS	read-only
			STATUS	current
			::= { hmWanMbus6A 31 }

hmWanMbus6AVIF0D		OBJECT-TYPE
			SYNTAX	INTEGER
			MAX-ACCESS	read-only
			STATUS	current
			::= { hmWanMbus6A 32 }

hmWanMbus6AValue0D		OBJECT-TYPE
			SYNTAX	INTEGER
			MAX-ACCESS	read-only
			STATUS	current
			::= { hmWanMbus6A 33 }

hmWanMbus6AVIF0E		OBJECT-TYPE
			SYNTAX	INTEGER
			MAX-ACCESS	read-only
			STATUS	current
			::= { hmWanMbus6A 34 }

hmWanMbus6AValue0E		OBJECT-TYPE
			SYNTAX	INTEGER
			MAX-ACCESS	read-only
			STATUS	current
			::= { hmWanMbus6A 35 }

hmWanMbus6AVIF0F		OBJECT-TYPE
			SYNTAX	INTEGER
			MAX-ACCESS	read-only
			STATUS	current
			::= { hmWanMbus6A 36 }

hmWanMbus6AValue0F		OBJECT-TYPE
			SYNTAX	INTEGER
			MAX-ACCESS	read-only
			STATUS	current
			::= { hmWanMbus6A 37 }

hmWanMbus6AVIF10		OBJECT-TYPE
			SYNTAX	INTEGER
			MAX-ACCESS	read-only
			STATUS	current
			::= { hmWanMbus6A 38 }

hmWanMbus6AValue10		OBJECT-TYPE
			SYNTAX	INTEGER
			MAX-ACCESS	read-only
			STATUS	current
			::= { hmWanMbus6A 39 }

hmWanMbus6AVIF11		OBJECT-TYPE
			SYNTAX	INTEGER
			MAX-ACCESS	read-only
			STATUS	current
			::= { hmWanMbus6A 40 }

hmWanMbus6AValue11		OBJECT-TYPE
			SYNTAX	INTEGER
			MAX-ACCESS	read-only
			STATUS	current
			::= { hmWanMbus6A 41 }

hmWanMbus6AVIF12		OBJECT-TYPE
			SYNTAX	INTEGER
			MAX-ACCESS	read-only
			STATUS	current
			::= { hmWanMbus6A 42 }

hmWanMbus6AValue12		OBJECT-TYPE
			SYNTAX	INTEGER
			MAX-ACCESS	read-only
			STATUS	current
			::= { hmWanMbus6A 43 }

hmWanMbus6AVIF13		OBJECT-TYPE
			SYNTAX	INTEGER
			MAX-ACCESS	read-only
			STATUS	current
			::= { hmWanMbus6A 44 }

hmWanMbus6AValue13		OBJECT-TYPE
			SYNTAX	INTEGER
			MAX-ACCESS	read-only
			STATUS	current
			::= { hmWanMbus6A 45 }

hmWanMbus6AVIF14		OBJECT-TYPE
			SYNTAX	INTEGER
			MAX-ACCESS	read-only
			STATUS	current
			::= { hmWanMbus6A 46 }

hmWanMbus6AValue14		OBJECT-TYPE
			SYNTAX	INTEGER
			MAX-ACCESS	read-only
			STATUS	current
			::= { hmWanMbus6A 47 }

hmWanMbus6AVIF15		OBJECT-TYPE
			SYNTAX	INTEGER
			MAX-ACCESS	read-only
			STATUS	current
			::= { hmWanMbus6A 48 }

hmWanMbus6AValue15		OBJECT-TYPE
			SYNTAX	INTEGER
			MAX-ACCESS	read-only
			STATUS	current
			::= { hmWanMbus6A 49 }

hmWanMbus6AVIF16		OBJECT-TYPE
			SYNTAX	INTEGER
			MAX-ACCESS	read-only
			STATUS	current
			::= { hmWanMbus6A 50 }

hmWanMbus6AValue16		OBJECT-TYPE
			SYNTAX	INTEGER
			MAX-ACCESS	read-only
			STATUS	current
			::= { hmWanMbus6A 51 }

hmWanMbus6AVIF17		OBJECT-TYPE
			SYNTAX	INTEGER
			MAX-ACCESS	read-only
			STATUS	current
			::= { hmWanMbus6A 52 }

hmWanMbus6AValue17		OBJECT-TYPE
			SYNTAX	INTEGER
			MAX-ACCESS	read-only
			STATUS	current
			::= { hmWanMbus6A 53 }

hmWanMbus6AVIF18		OBJECT-TYPE
			SYNTAX	INTEGER
			MAX-ACCESS	read-only
			STATUS	current
			::= { hmWanMbus6A 54 }

hmWanMbus6AValue18		OBJECT-TYPE
			SYNTAX	INTEGER
			MAX-ACCESS	read-only
			STATUS	current
			::= { hmWanMbus6A 55 }

hmWanMbus6AVIF19		OBJECT-TYPE
			SYNTAX	INTEGER
			MAX-ACCESS	read-only
			STATUS	current
			::= { hmWanMbus6A 56 }

hmWanMbus6AValue19		OBJECT-TYPE
			SYNTAX	INTEGER
			MAX-ACCESS	read-only
			STATUS	current
			::= { hmWanMbus6A 57 }

hmWanMbus6AVIF1A		OBJECT-TYPE
			SYNTAX	INTEGER
			MAX-ACCESS	read-only
			STATUS	current
			::= { hmWanMbus6A 58 }

hmWanMbus6AValue1A		OBJECT-TYPE
			SYNTAX	INTEGER
			MAX-ACCESS	read-only
			STATUS	current
			::= { hmWanMbus6A 59 }

hmWanMbus6AVIF1B		OBJECT-TYPE
			SYNTAX	INTEGER
			MAX-ACCESS	read-only
			STATUS	current
			::= { hmWanMbus6A 60 }

hmWanMbus6AValue1B		OBJECT-TYPE
			SYNTAX	INTEGER
			MAX-ACCESS	read-only
			STATUS	current
			::= { hmWanMbus6A 61 }

hmWanMbus6AVIF1C		OBJECT-TYPE
			SYNTAX	INTEGER
			MAX-ACCESS	read-only
			STATUS	current
			::= { hmWanMbus6A 62 }

hmWanMbus6AValue1C		OBJECT-TYPE
			SYNTAX	INTEGER
			MAX-ACCESS	read-only
			STATUS	current
			::= { hmWanMbus6A 63 }

hmWanMbus6AVIF1D		OBJECT-TYPE
			SYNTAX	INTEGER
			MAX-ACCESS	read-only
			STATUS	current
			::= { hmWanMbus6A 64 }

hmWanMbus6AValue1D		OBJECT-TYPE
			SYNTAX	INTEGER
			MAX-ACCESS	read-only
			STATUS	current
			::= { hmWanMbus6A 65 }

hmWanMbus6AVIF1E		OBJECT-TYPE
			SYNTAX	INTEGER
			MAX-ACCESS	read-only
			STATUS	current
			::= { hmWanMbus6A 66 }

hmWanMbus6AValue1E		OBJECT-TYPE
			SYNTAX	INTEGER
			MAX-ACCESS	read-only
			STATUS	current
			::= { hmWanMbus6A 67 }

hmWanMbus6AVIF1F		OBJECT-TYPE
			SYNTAX	INTEGER
			MAX-ACCESS	read-only
			STATUS	current
			::= { hmWanMbus6A 68 }

hmWanMbus6AValue1F		OBJECT-TYPE
			SYNTAX	INTEGER
			MAX-ACCESS	read-only
			STATUS	current
			::= { hmWanMbus6A 69 }

hmWanMbus6AVIF20		OBJECT-TYPE
			SYNTAX	INTEGER
			MAX-ACCESS	read-only
			STATUS	current
			::= { hmWanMbus6A 70 }

hmWanMbus6AValue20		OBJECT-TYPE
			SYNTAX	INTEGER
			MAX-ACCESS	read-only
			STATUS	current
			::= { hmWanMbus6A 71 }

hmWanMbus6AVIF21		OBJECT-TYPE
			SYNTAX	INTEGER
			MAX-ACCESS	read-only
			STATUS	current
			::= { hmWanMbus6A 72 }

hmWanMbus6AValue21		OBJECT-TYPE
			SYNTAX	INTEGER
			MAX-ACCESS	read-only
			STATUS	current
			::= { hmWanMbus6A 73 }

hmWanMbus6AVIF22		OBJECT-TYPE
			SYNTAX	INTEGER
			MAX-ACCESS	read-only
			STATUS	current
			::= { hmWanMbus6A 74 }

hmWanMbus6AValue22		OBJECT-TYPE
			SYNTAX	INTEGER
			MAX-ACCESS	read-only
			STATUS	current
			::= { hmWanMbus6A 75 }

hmWanMbus6AVIF23		OBJECT-TYPE
			SYNTAX	INTEGER
			MAX-ACCESS	read-only
			STATUS	current
			::= { hmWanMbus6A 76 }

hmWanMbus6AValue23		OBJECT-TYPE
			SYNTAX	INTEGER
			MAX-ACCESS	read-only
			STATUS	current
			::= { hmWanMbus6A 77 }

hmWanMbus6AVIF24		OBJECT-TYPE
			SYNTAX	INTEGER
			MAX-ACCESS	read-only
			STATUS	current
			::= { hmWanMbus6A 78 }

hmWanMbus6AValue24		OBJECT-TYPE
			SYNTAX	INTEGER
			MAX-ACCESS	read-only
			STATUS	current
			::= { hmWanMbus6A 79 }

hmWanMbus6AVIF25		OBJECT-TYPE
			SYNTAX	INTEGER
			MAX-ACCESS	read-only
			STATUS	current
			::= { hmWanMbus6A 80 }

hmWanMbus6AValue25		OBJECT-TYPE
			SYNTAX	INTEGER
			MAX-ACCESS	read-only
			STATUS	current
			::= { hmWanMbus6A 81 }

hmWanMbus6AVIF26		OBJECT-TYPE
			SYNTAX	INTEGER
			MAX-ACCESS	read-only
			STATUS	current
			::= { hmWanMbus6A 82 }

hmWanMbus6AValue26		OBJECT-TYPE
			SYNTAX	INTEGER
			MAX-ACCESS	read-only
			STATUS	current
			::= { hmWanMbus6A 83 }

hmWanMbus6AVIF27		OBJECT-TYPE
			SYNTAX	INTEGER
			MAX-ACCESS	read-only
			STATUS	current
			::= { hmWanMbus6A 84 }

hmWanMbus6AValue27		OBJECT-TYPE
			SYNTAX	INTEGER
			MAX-ACCESS	read-only
			STATUS	current
			::= { hmWanMbus6A 85 }

hmWanMbus6AVIF28		OBJECT-TYPE
			SYNTAX	INTEGER
			MAX-ACCESS	read-only
			STATUS	current
			::= { hmWanMbus6A 86 }

hmWanMbus6AValue28		OBJECT-TYPE
			SYNTAX	INTEGER
			MAX-ACCESS	read-only
			STATUS	current
			::= { hmWanMbus6A 87 }

hmWanMbus6AVIF29		OBJECT-TYPE
			SYNTAX	INTEGER
			MAX-ACCESS	read-only
			STATUS	current
			::= { hmWanMbus6A 88 }

hmWanMbus6AValue29		OBJECT-TYPE
			SYNTAX	INTEGER
			MAX-ACCESS	read-only
			STATUS	current
			::= { hmWanMbus6A 89 }

hmWanMbus6AVIF2A		OBJECT-TYPE
			SYNTAX	INTEGER
			MAX-ACCESS	read-only
			STATUS	current
			::= { hmWanMbus6A 90 }

hmWanMbus6AValue2A		OBJECT-TYPE
			SYNTAX	INTEGER
			MAX-ACCESS	read-only
			STATUS	current
			::= { hmWanMbus6A 91 }

hmWanMbus6AVIF2B		OBJECT-TYPE
			SYNTAX	INTEGER
			MAX-ACCESS	read-only
			STATUS	current
			::= { hmWanMbus6A 92 }

hmWanMbus6AValue2B		OBJECT-TYPE
			SYNTAX	INTEGER
			MAX-ACCESS	read-only
			STATUS	current
			::= { hmWanMbus6A 93 }

hmWanMbus6AVIF2C		OBJECT-TYPE
			SYNTAX	INTEGER
			MAX-ACCESS	read-only
			STATUS	current
			::= { hmWanMbus6A 94 }

hmWanMbus6AValue2C		OBJECT-TYPE
			SYNTAX	INTEGER
			MAX-ACCESS	read-only
			STATUS	current
			::= { hmWanMbus6A 95 }

hmWanMbus6AVIF2D		OBJECT-TYPE
			SYNTAX	INTEGER
			MAX-ACCESS	read-only
			STATUS	current
			::= { hmWanMbus6A 96 }

hmWanMbus6AValue2D		OBJECT-TYPE
			SYNTAX	INTEGER
			MAX-ACCESS	read-only
			STATUS	current
			::= { hmWanMbus6A 97 }

hmWanMbus6AVIF2E		OBJECT-TYPE
			SYNTAX	INTEGER
			MAX-ACCESS	read-only
			STATUS	current
			::= { hmWanMbus6A 98 }

hmWanMbus6AValue2E		OBJECT-TYPE
			SYNTAX	INTEGER
			MAX-ACCESS	read-only
			STATUS	current
			::= { hmWanMbus6A 99 }

hmWanMbus6AVIF2F		OBJECT-TYPE
			SYNTAX	INTEGER
			MAX-ACCESS	read-only
			STATUS	current
			::= { hmWanMbus6A 100 }

hmWanMbus6AValue2F		OBJECT-TYPE
			SYNTAX	INTEGER
			MAX-ACCESS	read-only
			STATUS	current
			::= { hmWanMbus6A 101 }

hmWanMbus6B			OBJECT IDENTIFIER ::= { hmWanMbus 107 }

hmWanMbus6BIdNumber		OBJECT-TYPE
			SYNTAX	Gauge32
			MAX-ACCESS	read-only
			STATUS	current
			::= { hmWanMbus6B 1 }

hmWanMbus6BManufacturer	OBJECT-TYPE
			SYNTAX	Gauge32
			MAX-ACCESS	read-only
			STATUS	current
			::= { hmWanMbus6B 2 }

hmWanMbus6BVersion		OBJECT-TYPE
			SYNTAX	Gauge32
			MAX-ACCESS	read-only
			STATUS	current
			::= { hmWanMbus6B 3 }

hmWanMbus6BMedium		OBJECT-TYPE
			SYNTAX	Gauge32
			MAX-ACCESS	read-only
			STATUS	current
			::= { hmWanMbus6B 4 }

hmWanMbus6BStatus		OBJECT-TYPE
			SYNTAX	Gauge32
			MAX-ACCESS	read-only
			STATUS	current
			::= { hmWanMbus6B 5 }

hmWanMbus6BVIF00		OBJECT-TYPE
			SYNTAX	INTEGER
			MAX-ACCESS	read-only
			STATUS	current
			::= { hmWanMbus6B 6 }

hmWanMbus6BValue00		OBJECT-TYPE
			SYNTAX	INTEGER
			MAX-ACCESS	read-only
			STATUS	current
			::= { hmWanMbus6B 7 }

hmWanMbus6BVIF01		OBJECT-TYPE
			SYNTAX	INTEGER
			MAX-ACCESS	read-only
			STATUS	current
			::= { hmWanMbus6B 8 }

hmWanMbus6BValue01		OBJECT-TYPE
			SYNTAX	INTEGER
			MAX-ACCESS	read-only
			STATUS	current
			::= { hmWanMbus6B 9 }

hmWanMbus6BVIF02		OBJECT-TYPE
			SYNTAX	INTEGER
			MAX-ACCESS	read-only
			STATUS	current
			::= { hmWanMbus6B 10 }

hmWanMbus6BValue02		OBJECT-TYPE
			SYNTAX	INTEGER
			MAX-ACCESS	read-only
			STATUS	current
			::= { hmWanMbus6B 11 }

hmWanMbus6BVIF03		OBJECT-TYPE
			SYNTAX	INTEGER
			MAX-ACCESS	read-only
			STATUS	current
			::= { hmWanMbus6B 12 }

hmWanMbus6BValue03		OBJECT-TYPE
			SYNTAX	INTEGER
			MAX-ACCESS	read-only
			STATUS	current
			::= { hmWanMbus6B 13 }

hmWanMbus6BVIF04		OBJECT-TYPE
			SYNTAX	INTEGER
			MAX-ACCESS	read-only
			STATUS	current
			::= { hmWanMbus6B 14 }

hmWanMbus6BValue04		OBJECT-TYPE
			SYNTAX	INTEGER
			MAX-ACCESS	read-only
			STATUS	current
			::= { hmWanMbus6B 15 }

hmWanMbus6BVIF05		OBJECT-TYPE
			SYNTAX	INTEGER
			MAX-ACCESS	read-only
			STATUS	current
			::= { hmWanMbus6B 16 }

hmWanMbus6BValue05		OBJECT-TYPE
			SYNTAX	INTEGER
			MAX-ACCESS	read-only
			STATUS	current
			::= { hmWanMbus6B 17 }

hmWanMbus6BVIF06		OBJECT-TYPE
			SYNTAX	INTEGER
			MAX-ACCESS	read-only
			STATUS	current
			::= { hmWanMbus6B 18 }

hmWanMbus6BValue06		OBJECT-TYPE
			SYNTAX	INTEGER
			MAX-ACCESS	read-only
			STATUS	current
			::= { hmWanMbus6B 19 }

hmWanMbus6BVIF07		OBJECT-TYPE
			SYNTAX	INTEGER
			MAX-ACCESS	read-only
			STATUS	current
			::= { hmWanMbus6B 20 }

hmWanMbus6BValue07		OBJECT-TYPE
			SYNTAX	INTEGER
			MAX-ACCESS	read-only
			STATUS	current
			::= { hmWanMbus6B 21 }

hmWanMbus6BVIF08		OBJECT-TYPE
			SYNTAX	INTEGER
			MAX-ACCESS	read-only
			STATUS	current
			::= { hmWanMbus6B 22 }

hmWanMbus6BValue08		OBJECT-TYPE
			SYNTAX	INTEGER
			MAX-ACCESS	read-only
			STATUS	current
			::= { hmWanMbus6B 23 }

hmWanMbus6BVIF09		OBJECT-TYPE
			SYNTAX	INTEGER
			MAX-ACCESS	read-only
			STATUS	current
			::= { hmWanMbus6B 24 }

hmWanMbus6BValue09		OBJECT-TYPE
			SYNTAX	INTEGER
			MAX-ACCESS	read-only
			STATUS	current
			::= { hmWanMbus6B 25 }

hmWanMbus6BVIF0A		OBJECT-TYPE
			SYNTAX	INTEGER
			MAX-ACCESS	read-only
			STATUS	current
			::= { hmWanMbus6B 26 }

hmWanMbus6BValue0A		OBJECT-TYPE
			SYNTAX	INTEGER
			MAX-ACCESS	read-only
			STATUS	current
			::= { hmWanMbus6B 27 }

hmWanMbus6BVIF0B		OBJECT-TYPE
			SYNTAX	INTEGER
			MAX-ACCESS	read-only
			STATUS	current
			::= { hmWanMbus6B 28 }

hmWanMbus6BValue0B		OBJECT-TYPE
			SYNTAX	INTEGER
			MAX-ACCESS	read-only
			STATUS	current
			::= { hmWanMbus6B 29 }

hmWanMbus6BVIF0C		OBJECT-TYPE
			SYNTAX	INTEGER
			MAX-ACCESS	read-only
			STATUS	current
			::= { hmWanMbus6B 30 }

hmWanMbus6BValue0C		OBJECT-TYPE
			SYNTAX	INTEGER
			MAX-ACCESS	read-only
			STATUS	current
			::= { hmWanMbus6B 31 }

hmWanMbus6BVIF0D		OBJECT-TYPE
			SYNTAX	INTEGER
			MAX-ACCESS	read-only
			STATUS	current
			::= { hmWanMbus6B 32 }

hmWanMbus6BValue0D		OBJECT-TYPE
			SYNTAX	INTEGER
			MAX-ACCESS	read-only
			STATUS	current
			::= { hmWanMbus6B 33 }

hmWanMbus6BVIF0E		OBJECT-TYPE
			SYNTAX	INTEGER
			MAX-ACCESS	read-only
			STATUS	current
			::= { hmWanMbus6B 34 }

hmWanMbus6BValue0E		OBJECT-TYPE
			SYNTAX	INTEGER
			MAX-ACCESS	read-only
			STATUS	current
			::= { hmWanMbus6B 35 }

hmWanMbus6BVIF0F		OBJECT-TYPE
			SYNTAX	INTEGER
			MAX-ACCESS	read-only
			STATUS	current
			::= { hmWanMbus6B 36 }

hmWanMbus6BValue0F		OBJECT-TYPE
			SYNTAX	INTEGER
			MAX-ACCESS	read-only
			STATUS	current
			::= { hmWanMbus6B 37 }

hmWanMbus6BVIF10		OBJECT-TYPE
			SYNTAX	INTEGER
			MAX-ACCESS	read-only
			STATUS	current
			::= { hmWanMbus6B 38 }

hmWanMbus6BValue10		OBJECT-TYPE
			SYNTAX	INTEGER
			MAX-ACCESS	read-only
			STATUS	current
			::= { hmWanMbus6B 39 }

hmWanMbus6BVIF11		OBJECT-TYPE
			SYNTAX	INTEGER
			MAX-ACCESS	read-only
			STATUS	current
			::= { hmWanMbus6B 40 }

hmWanMbus6BValue11		OBJECT-TYPE
			SYNTAX	INTEGER
			MAX-ACCESS	read-only
			STATUS	current
			::= { hmWanMbus6B 41 }

hmWanMbus6BVIF12		OBJECT-TYPE
			SYNTAX	INTEGER
			MAX-ACCESS	read-only
			STATUS	current
			::= { hmWanMbus6B 42 }

hmWanMbus6BValue12		OBJECT-TYPE
			SYNTAX	INTEGER
			MAX-ACCESS	read-only
			STATUS	current
			::= { hmWanMbus6B 43 }

hmWanMbus6BVIF13		OBJECT-TYPE
			SYNTAX	INTEGER
			MAX-ACCESS	read-only
			STATUS	current
			::= { hmWanMbus6B 44 }

hmWanMbus6BValue13		OBJECT-TYPE
			SYNTAX	INTEGER
			MAX-ACCESS	read-only
			STATUS	current
			::= { hmWanMbus6B 45 }

hmWanMbus6BVIF14		OBJECT-TYPE
			SYNTAX	INTEGER
			MAX-ACCESS	read-only
			STATUS	current
			::= { hmWanMbus6B 46 }

hmWanMbus6BValue14		OBJECT-TYPE
			SYNTAX	INTEGER
			MAX-ACCESS	read-only
			STATUS	current
			::= { hmWanMbus6B 47 }

hmWanMbus6BVIF15		OBJECT-TYPE
			SYNTAX	INTEGER
			MAX-ACCESS	read-only
			STATUS	current
			::= { hmWanMbus6B 48 }

hmWanMbus6BValue15		OBJECT-TYPE
			SYNTAX	INTEGER
			MAX-ACCESS	read-only
			STATUS	current
			::= { hmWanMbus6B 49 }

hmWanMbus6BVIF16		OBJECT-TYPE
			SYNTAX	INTEGER
			MAX-ACCESS	read-only
			STATUS	current
			::= { hmWanMbus6B 50 }

hmWanMbus6BValue16		OBJECT-TYPE
			SYNTAX	INTEGER
			MAX-ACCESS	read-only
			STATUS	current
			::= { hmWanMbus6B 51 }

hmWanMbus6BVIF17		OBJECT-TYPE
			SYNTAX	INTEGER
			MAX-ACCESS	read-only
			STATUS	current
			::= { hmWanMbus6B 52 }

hmWanMbus6BValue17		OBJECT-TYPE
			SYNTAX	INTEGER
			MAX-ACCESS	read-only
			STATUS	current
			::= { hmWanMbus6B 53 }

hmWanMbus6BVIF18		OBJECT-TYPE
			SYNTAX	INTEGER
			MAX-ACCESS	read-only
			STATUS	current
			::= { hmWanMbus6B 54 }

hmWanMbus6BValue18		OBJECT-TYPE
			SYNTAX	INTEGER
			MAX-ACCESS	read-only
			STATUS	current
			::= { hmWanMbus6B 55 }

hmWanMbus6BVIF19		OBJECT-TYPE
			SYNTAX	INTEGER
			MAX-ACCESS	read-only
			STATUS	current
			::= { hmWanMbus6B 56 }

hmWanMbus6BValue19		OBJECT-TYPE
			SYNTAX	INTEGER
			MAX-ACCESS	read-only
			STATUS	current
			::= { hmWanMbus6B 57 }

hmWanMbus6BVIF1A		OBJECT-TYPE
			SYNTAX	INTEGER
			MAX-ACCESS	read-only
			STATUS	current
			::= { hmWanMbus6B 58 }

hmWanMbus6BValue1A		OBJECT-TYPE
			SYNTAX	INTEGER
			MAX-ACCESS	read-only
			STATUS	current
			::= { hmWanMbus6B 59 }

hmWanMbus6BVIF1B		OBJECT-TYPE
			SYNTAX	INTEGER
			MAX-ACCESS	read-only
			STATUS	current
			::= { hmWanMbus6B 60 }

hmWanMbus6BValue1B		OBJECT-TYPE
			SYNTAX	INTEGER
			MAX-ACCESS	read-only
			STATUS	current
			::= { hmWanMbus6B 61 }

hmWanMbus6BVIF1C		OBJECT-TYPE
			SYNTAX	INTEGER
			MAX-ACCESS	read-only
			STATUS	current
			::= { hmWanMbus6B 62 }

hmWanMbus6BValue1C		OBJECT-TYPE
			SYNTAX	INTEGER
			MAX-ACCESS	read-only
			STATUS	current
			::= { hmWanMbus6B 63 }

hmWanMbus6BVIF1D		OBJECT-TYPE
			SYNTAX	INTEGER
			MAX-ACCESS	read-only
			STATUS	current
			::= { hmWanMbus6B 64 }

hmWanMbus6BValue1D		OBJECT-TYPE
			SYNTAX	INTEGER
			MAX-ACCESS	read-only
			STATUS	current
			::= { hmWanMbus6B 65 }

hmWanMbus6BVIF1E		OBJECT-TYPE
			SYNTAX	INTEGER
			MAX-ACCESS	read-only
			STATUS	current
			::= { hmWanMbus6B 66 }

hmWanMbus6BValue1E		OBJECT-TYPE
			SYNTAX	INTEGER
			MAX-ACCESS	read-only
			STATUS	current
			::= { hmWanMbus6B 67 }

hmWanMbus6BVIF1F		OBJECT-TYPE
			SYNTAX	INTEGER
			MAX-ACCESS	read-only
			STATUS	current
			::= { hmWanMbus6B 68 }

hmWanMbus6BValue1F		OBJECT-TYPE
			SYNTAX	INTEGER
			MAX-ACCESS	read-only
			STATUS	current
			::= { hmWanMbus6B 69 }

hmWanMbus6BVIF20		OBJECT-TYPE
			SYNTAX	INTEGER
			MAX-ACCESS	read-only
			STATUS	current
			::= { hmWanMbus6B 70 }

hmWanMbus6BValue20		OBJECT-TYPE
			SYNTAX	INTEGER
			MAX-ACCESS	read-only
			STATUS	current
			::= { hmWanMbus6B 71 }

hmWanMbus6BVIF21		OBJECT-TYPE
			SYNTAX	INTEGER
			MAX-ACCESS	read-only
			STATUS	current
			::= { hmWanMbus6B 72 }

hmWanMbus6BValue21		OBJECT-TYPE
			SYNTAX	INTEGER
			MAX-ACCESS	read-only
			STATUS	current
			::= { hmWanMbus6B 73 }

hmWanMbus6BVIF22		OBJECT-TYPE
			SYNTAX	INTEGER
			MAX-ACCESS	read-only
			STATUS	current
			::= { hmWanMbus6B 74 }

hmWanMbus6BValue22		OBJECT-TYPE
			SYNTAX	INTEGER
			MAX-ACCESS	read-only
			STATUS	current
			::= { hmWanMbus6B 75 }

hmWanMbus6BVIF23		OBJECT-TYPE
			SYNTAX	INTEGER
			MAX-ACCESS	read-only
			STATUS	current
			::= { hmWanMbus6B 76 }

hmWanMbus6BValue23		OBJECT-TYPE
			SYNTAX	INTEGER
			MAX-ACCESS	read-only
			STATUS	current
			::= { hmWanMbus6B 77 }

hmWanMbus6BVIF24		OBJECT-TYPE
			SYNTAX	INTEGER
			MAX-ACCESS	read-only
			STATUS	current
			::= { hmWanMbus6B 78 }

hmWanMbus6BValue24		OBJECT-TYPE
			SYNTAX	INTEGER
			MAX-ACCESS	read-only
			STATUS	current
			::= { hmWanMbus6B 79 }

hmWanMbus6BVIF25		OBJECT-TYPE
			SYNTAX	INTEGER
			MAX-ACCESS	read-only
			STATUS	current
			::= { hmWanMbus6B 80 }

hmWanMbus6BValue25		OBJECT-TYPE
			SYNTAX	INTEGER
			MAX-ACCESS	read-only
			STATUS	current
			::= { hmWanMbus6B 81 }

hmWanMbus6BVIF26		OBJECT-TYPE
			SYNTAX	INTEGER
			MAX-ACCESS	read-only
			STATUS	current
			::= { hmWanMbus6B 82 }

hmWanMbus6BValue26		OBJECT-TYPE
			SYNTAX	INTEGER
			MAX-ACCESS	read-only
			STATUS	current
			::= { hmWanMbus6B 83 }

hmWanMbus6BVIF27		OBJECT-TYPE
			SYNTAX	INTEGER
			MAX-ACCESS	read-only
			STATUS	current
			::= { hmWanMbus6B 84 }

hmWanMbus6BValue27		OBJECT-TYPE
			SYNTAX	INTEGER
			MAX-ACCESS	read-only
			STATUS	current
			::= { hmWanMbus6B 85 }

hmWanMbus6BVIF28		OBJECT-TYPE
			SYNTAX	INTEGER
			MAX-ACCESS	read-only
			STATUS	current
			::= { hmWanMbus6B 86 }

hmWanMbus6BValue28		OBJECT-TYPE
			SYNTAX	INTEGER
			MAX-ACCESS	read-only
			STATUS	current
			::= { hmWanMbus6B 87 }

hmWanMbus6BVIF29		OBJECT-TYPE
			SYNTAX	INTEGER
			MAX-ACCESS	read-only
			STATUS	current
			::= { hmWanMbus6B 88 }

hmWanMbus6BValue29		OBJECT-TYPE
			SYNTAX	INTEGER
			MAX-ACCESS	read-only
			STATUS	current
			::= { hmWanMbus6B 89 }

hmWanMbus6BVIF2A		OBJECT-TYPE
			SYNTAX	INTEGER
			MAX-ACCESS	read-only
			STATUS	current
			::= { hmWanMbus6B 90 }

hmWanMbus6BValue2A		OBJECT-TYPE
			SYNTAX	INTEGER
			MAX-ACCESS	read-only
			STATUS	current
			::= { hmWanMbus6B 91 }

hmWanMbus6BVIF2B		OBJECT-TYPE
			SYNTAX	INTEGER
			MAX-ACCESS	read-only
			STATUS	current
			::= { hmWanMbus6B 92 }

hmWanMbus6BValue2B		OBJECT-TYPE
			SYNTAX	INTEGER
			MAX-ACCESS	read-only
			STATUS	current
			::= { hmWanMbus6B 93 }

hmWanMbus6BVIF2C		OBJECT-TYPE
			SYNTAX	INTEGER
			MAX-ACCESS	read-only
			STATUS	current
			::= { hmWanMbus6B 94 }

hmWanMbus6BValue2C		OBJECT-TYPE
			SYNTAX	INTEGER
			MAX-ACCESS	read-only
			STATUS	current
			::= { hmWanMbus6B 95 }

hmWanMbus6BVIF2D		OBJECT-TYPE
			SYNTAX	INTEGER
			MAX-ACCESS	read-only
			STATUS	current
			::= { hmWanMbus6B 96 }

hmWanMbus6BValue2D		OBJECT-TYPE
			SYNTAX	INTEGER
			MAX-ACCESS	read-only
			STATUS	current
			::= { hmWanMbus6B 97 }

hmWanMbus6BVIF2E		OBJECT-TYPE
			SYNTAX	INTEGER
			MAX-ACCESS	read-only
			STATUS	current
			::= { hmWanMbus6B 98 }

hmWanMbus6BValue2E		OBJECT-TYPE
			SYNTAX	INTEGER
			MAX-ACCESS	read-only
			STATUS	current
			::= { hmWanMbus6B 99 }

hmWanMbus6BVIF2F		OBJECT-TYPE
			SYNTAX	INTEGER
			MAX-ACCESS	read-only
			STATUS	current
			::= { hmWanMbus6B 100 }

hmWanMbus6BValue2F		OBJECT-TYPE
			SYNTAX	INTEGER
			MAX-ACCESS	read-only
			STATUS	current
			::= { hmWanMbus6B 101 }

hmWanMbus6C			OBJECT IDENTIFIER ::= { hmWanMbus 108 }

hmWanMbus6CIdNumber		OBJECT-TYPE
			SYNTAX	Gauge32
			MAX-ACCESS	read-only
			STATUS	current
			::= { hmWanMbus6C 1 }

hmWanMbus6CManufacturer	OBJECT-TYPE
			SYNTAX	Gauge32
			MAX-ACCESS	read-only
			STATUS	current
			::= { hmWanMbus6C 2 }

hmWanMbus6CVersion		OBJECT-TYPE
			SYNTAX	Gauge32
			MAX-ACCESS	read-only
			STATUS	current
			::= { hmWanMbus6C 3 }

hmWanMbus6CMedium		OBJECT-TYPE
			SYNTAX	Gauge32
			MAX-ACCESS	read-only
			STATUS	current
			::= { hmWanMbus6C 4 }

hmWanMbus6CStatus		OBJECT-TYPE
			SYNTAX	Gauge32
			MAX-ACCESS	read-only
			STATUS	current
			::= { hmWanMbus6C 5 }

hmWanMbus6CVIF00		OBJECT-TYPE
			SYNTAX	INTEGER
			MAX-ACCESS	read-only
			STATUS	current
			::= { hmWanMbus6C 6 }

hmWanMbus6CValue00		OBJECT-TYPE
			SYNTAX	INTEGER
			MAX-ACCESS	read-only
			STATUS	current
			::= { hmWanMbus6C 7 }

hmWanMbus6CVIF01		OBJECT-TYPE
			SYNTAX	INTEGER
			MAX-ACCESS	read-only
			STATUS	current
			::= { hmWanMbus6C 8 }

hmWanMbus6CValue01		OBJECT-TYPE
			SYNTAX	INTEGER
			MAX-ACCESS	read-only
			STATUS	current
			::= { hmWanMbus6C 9 }

hmWanMbus6CVIF02		OBJECT-TYPE
			SYNTAX	INTEGER
			MAX-ACCESS	read-only
			STATUS	current
			::= { hmWanMbus6C 10 }

hmWanMbus6CValue02		OBJECT-TYPE
			SYNTAX	INTEGER
			MAX-ACCESS	read-only
			STATUS	current
			::= { hmWanMbus6C 11 }

hmWanMbus6CVIF03		OBJECT-TYPE
			SYNTAX	INTEGER
			MAX-ACCESS	read-only
			STATUS	current
			::= { hmWanMbus6C 12 }

hmWanMbus6CValue03		OBJECT-TYPE
			SYNTAX	INTEGER
			MAX-ACCESS	read-only
			STATUS	current
			::= { hmWanMbus6C 13 }

hmWanMbus6CVIF04		OBJECT-TYPE
			SYNTAX	INTEGER
			MAX-ACCESS	read-only
			STATUS	current
			::= { hmWanMbus6C 14 }

hmWanMbus6CValue04		OBJECT-TYPE
			SYNTAX	INTEGER
			MAX-ACCESS	read-only
			STATUS	current
			::= { hmWanMbus6C 15 }

hmWanMbus6CVIF05		OBJECT-TYPE
			SYNTAX	INTEGER
			MAX-ACCESS	read-only
			STATUS	current
			::= { hmWanMbus6C 16 }

hmWanMbus6CValue05		OBJECT-TYPE
			SYNTAX	INTEGER
			MAX-ACCESS	read-only
			STATUS	current
			::= { hmWanMbus6C 17 }

hmWanMbus6CVIF06		OBJECT-TYPE
			SYNTAX	INTEGER
			MAX-ACCESS	read-only
			STATUS	current
			::= { hmWanMbus6C 18 }

hmWanMbus6CValue06		OBJECT-TYPE
			SYNTAX	INTEGER
			MAX-ACCESS	read-only
			STATUS	current
			::= { hmWanMbus6C 19 }

hmWanMbus6CVIF07		OBJECT-TYPE
			SYNTAX	INTEGER
			MAX-ACCESS	read-only
			STATUS	current
			::= { hmWanMbus6C 20 }

hmWanMbus6CValue07		OBJECT-TYPE
			SYNTAX	INTEGER
			MAX-ACCESS	read-only
			STATUS	current
			::= { hmWanMbus6C 21 }

hmWanMbus6CVIF08		OBJECT-TYPE
			SYNTAX	INTEGER
			MAX-ACCESS	read-only
			STATUS	current
			::= { hmWanMbus6C 22 }

hmWanMbus6CValue08		OBJECT-TYPE
			SYNTAX	INTEGER
			MAX-ACCESS	read-only
			STATUS	current
			::= { hmWanMbus6C 23 }

hmWanMbus6CVIF09		OBJECT-TYPE
			SYNTAX	INTEGER
			MAX-ACCESS	read-only
			STATUS	current
			::= { hmWanMbus6C 24 }

hmWanMbus6CValue09		OBJECT-TYPE
			SYNTAX	INTEGER
			MAX-ACCESS	read-only
			STATUS	current
			::= { hmWanMbus6C 25 }

hmWanMbus6CVIF0A		OBJECT-TYPE
			SYNTAX	INTEGER
			MAX-ACCESS	read-only
			STATUS	current
			::= { hmWanMbus6C 26 }

hmWanMbus6CValue0A		OBJECT-TYPE
			SYNTAX	INTEGER
			MAX-ACCESS	read-only
			STATUS	current
			::= { hmWanMbus6C 27 }

hmWanMbus6CVIF0B		OBJECT-TYPE
			SYNTAX	INTEGER
			MAX-ACCESS	read-only
			STATUS	current
			::= { hmWanMbus6C 28 }

hmWanMbus6CValue0B		OBJECT-TYPE
			SYNTAX	INTEGER
			MAX-ACCESS	read-only
			STATUS	current
			::= { hmWanMbus6C 29 }

hmWanMbus6CVIF0C		OBJECT-TYPE
			SYNTAX	INTEGER
			MAX-ACCESS	read-only
			STATUS	current
			::= { hmWanMbus6C 30 }

hmWanMbus6CValue0C		OBJECT-TYPE
			SYNTAX	INTEGER
			MAX-ACCESS	read-only
			STATUS	current
			::= { hmWanMbus6C 31 }

hmWanMbus6CVIF0D		OBJECT-TYPE
			SYNTAX	INTEGER
			MAX-ACCESS	read-only
			STATUS	current
			::= { hmWanMbus6C 32 }

hmWanMbus6CValue0D		OBJECT-TYPE
			SYNTAX	INTEGER
			MAX-ACCESS	read-only
			STATUS	current
			::= { hmWanMbus6C 33 }

hmWanMbus6CVIF0E		OBJECT-TYPE
			SYNTAX	INTEGER
			MAX-ACCESS	read-only
			STATUS	current
			::= { hmWanMbus6C 34 }

hmWanMbus6CValue0E		OBJECT-TYPE
			SYNTAX	INTEGER
			MAX-ACCESS	read-only
			STATUS	current
			::= { hmWanMbus6C 35 }

hmWanMbus6CVIF0F		OBJECT-TYPE
			SYNTAX	INTEGER
			MAX-ACCESS	read-only
			STATUS	current
			::= { hmWanMbus6C 36 }

hmWanMbus6CValue0F		OBJECT-TYPE
			SYNTAX	INTEGER
			MAX-ACCESS	read-only
			STATUS	current
			::= { hmWanMbus6C 37 }

hmWanMbus6CVIF10		OBJECT-TYPE
			SYNTAX	INTEGER
			MAX-ACCESS	read-only
			STATUS	current
			::= { hmWanMbus6C 38 }

hmWanMbus6CValue10		OBJECT-TYPE
			SYNTAX	INTEGER
			MAX-ACCESS	read-only
			STATUS	current
			::= { hmWanMbus6C 39 }

hmWanMbus6CVIF11		OBJECT-TYPE
			SYNTAX	INTEGER
			MAX-ACCESS	read-only
			STATUS	current
			::= { hmWanMbus6C 40 }

hmWanMbus6CValue11		OBJECT-TYPE
			SYNTAX	INTEGER
			MAX-ACCESS	read-only
			STATUS	current
			::= { hmWanMbus6C 41 }

hmWanMbus6CVIF12		OBJECT-TYPE
			SYNTAX	INTEGER
			MAX-ACCESS	read-only
			STATUS	current
			::= { hmWanMbus6C 42 }

hmWanMbus6CValue12		OBJECT-TYPE
			SYNTAX	INTEGER
			MAX-ACCESS	read-only
			STATUS	current
			::= { hmWanMbus6C 43 }

hmWanMbus6CVIF13		OBJECT-TYPE
			SYNTAX	INTEGER
			MAX-ACCESS	read-only
			STATUS	current
			::= { hmWanMbus6C 44 }

hmWanMbus6CValue13		OBJECT-TYPE
			SYNTAX	INTEGER
			MAX-ACCESS	read-only
			STATUS	current
			::= { hmWanMbus6C 45 }

hmWanMbus6CVIF14		OBJECT-TYPE
			SYNTAX	INTEGER
			MAX-ACCESS	read-only
			STATUS	current
			::= { hmWanMbus6C 46 }

hmWanMbus6CValue14		OBJECT-TYPE
			SYNTAX	INTEGER
			MAX-ACCESS	read-only
			STATUS	current
			::= { hmWanMbus6C 47 }

hmWanMbus6CVIF15		OBJECT-TYPE
			SYNTAX	INTEGER
			MAX-ACCESS	read-only
			STATUS	current
			::= { hmWanMbus6C 48 }

hmWanMbus6CValue15		OBJECT-TYPE
			SYNTAX	INTEGER
			MAX-ACCESS	read-only
			STATUS	current
			::= { hmWanMbus6C 49 }

hmWanMbus6CVIF16		OBJECT-TYPE
			SYNTAX	INTEGER
			MAX-ACCESS	read-only
			STATUS	current
			::= { hmWanMbus6C 50 }

hmWanMbus6CValue16		OBJECT-TYPE
			SYNTAX	INTEGER
			MAX-ACCESS	read-only
			STATUS	current
			::= { hmWanMbus6C 51 }

hmWanMbus6CVIF17		OBJECT-TYPE
			SYNTAX	INTEGER
			MAX-ACCESS	read-only
			STATUS	current
			::= { hmWanMbus6C 52 }

hmWanMbus6CValue17		OBJECT-TYPE
			SYNTAX	INTEGER
			MAX-ACCESS	read-only
			STATUS	current
			::= { hmWanMbus6C 53 }

hmWanMbus6CVIF18		OBJECT-TYPE
			SYNTAX	INTEGER
			MAX-ACCESS	read-only
			STATUS	current
			::= { hmWanMbus6C 54 }

hmWanMbus6CValue18		OBJECT-TYPE
			SYNTAX	INTEGER
			MAX-ACCESS	read-only
			STATUS	current
			::= { hmWanMbus6C 55 }

hmWanMbus6CVIF19		OBJECT-TYPE
			SYNTAX	INTEGER
			MAX-ACCESS	read-only
			STATUS	current
			::= { hmWanMbus6C 56 }

hmWanMbus6CValue19		OBJECT-TYPE
			SYNTAX	INTEGER
			MAX-ACCESS	read-only
			STATUS	current
			::= { hmWanMbus6C 57 }

hmWanMbus6CVIF1A		OBJECT-TYPE
			SYNTAX	INTEGER
			MAX-ACCESS	read-only
			STATUS	current
			::= { hmWanMbus6C 58 }

hmWanMbus6CValue1A		OBJECT-TYPE
			SYNTAX	INTEGER
			MAX-ACCESS	read-only
			STATUS	current
			::= { hmWanMbus6C 59 }

hmWanMbus6CVIF1B		OBJECT-TYPE
			SYNTAX	INTEGER
			MAX-ACCESS	read-only
			STATUS	current
			::= { hmWanMbus6C 60 }

hmWanMbus6CValue1B		OBJECT-TYPE
			SYNTAX	INTEGER
			MAX-ACCESS	read-only
			STATUS	current
			::= { hmWanMbus6C 61 }

hmWanMbus6CVIF1C		OBJECT-TYPE
			SYNTAX	INTEGER
			MAX-ACCESS	read-only
			STATUS	current
			::= { hmWanMbus6C 62 }

hmWanMbus6CValue1C		OBJECT-TYPE
			SYNTAX	INTEGER
			MAX-ACCESS	read-only
			STATUS	current
			::= { hmWanMbus6C 63 }

hmWanMbus6CVIF1D		OBJECT-TYPE
			SYNTAX	INTEGER
			MAX-ACCESS	read-only
			STATUS	current
			::= { hmWanMbus6C 64 }

hmWanMbus6CValue1D		OBJECT-TYPE
			SYNTAX	INTEGER
			MAX-ACCESS	read-only
			STATUS	current
			::= { hmWanMbus6C 65 }

hmWanMbus6CVIF1E		OBJECT-TYPE
			SYNTAX	INTEGER
			MAX-ACCESS	read-only
			STATUS	current
			::= { hmWanMbus6C 66 }

hmWanMbus6CValue1E		OBJECT-TYPE
			SYNTAX	INTEGER
			MAX-ACCESS	read-only
			STATUS	current
			::= { hmWanMbus6C 67 }

hmWanMbus6CVIF1F		OBJECT-TYPE
			SYNTAX	INTEGER
			MAX-ACCESS	read-only
			STATUS	current
			::= { hmWanMbus6C 68 }

hmWanMbus6CValue1F		OBJECT-TYPE
			SYNTAX	INTEGER
			MAX-ACCESS	read-only
			STATUS	current
			::= { hmWanMbus6C 69 }

hmWanMbus6CVIF20		OBJECT-TYPE
			SYNTAX	INTEGER
			MAX-ACCESS	read-only
			STATUS	current
			::= { hmWanMbus6C 70 }

hmWanMbus6CValue20		OBJECT-TYPE
			SYNTAX	INTEGER
			MAX-ACCESS	read-only
			STATUS	current
			::= { hmWanMbus6C 71 }

hmWanMbus6CVIF21		OBJECT-TYPE
			SYNTAX	INTEGER
			MAX-ACCESS	read-only
			STATUS	current
			::= { hmWanMbus6C 72 }

hmWanMbus6CValue21		OBJECT-TYPE
			SYNTAX	INTEGER
			MAX-ACCESS	read-only
			STATUS	current
			::= { hmWanMbus6C 73 }

hmWanMbus6CVIF22		OBJECT-TYPE
			SYNTAX	INTEGER
			MAX-ACCESS	read-only
			STATUS	current
			::= { hmWanMbus6C 74 }

hmWanMbus6CValue22		OBJECT-TYPE
			SYNTAX	INTEGER
			MAX-ACCESS	read-only
			STATUS	current
			::= { hmWanMbus6C 75 }

hmWanMbus6CVIF23		OBJECT-TYPE
			SYNTAX	INTEGER
			MAX-ACCESS	read-only
			STATUS	current
			::= { hmWanMbus6C 76 }

hmWanMbus6CValue23		OBJECT-TYPE
			SYNTAX	INTEGER
			MAX-ACCESS	read-only
			STATUS	current
			::= { hmWanMbus6C 77 }

hmWanMbus6CVIF24		OBJECT-TYPE
			SYNTAX	INTEGER
			MAX-ACCESS	read-only
			STATUS	current
			::= { hmWanMbus6C 78 }

hmWanMbus6CValue24		OBJECT-TYPE
			SYNTAX	INTEGER
			MAX-ACCESS	read-only
			STATUS	current
			::= { hmWanMbus6C 79 }

hmWanMbus6CVIF25		OBJECT-TYPE
			SYNTAX	INTEGER
			MAX-ACCESS	read-only
			STATUS	current
			::= { hmWanMbus6C 80 }

hmWanMbus6CValue25		OBJECT-TYPE
			SYNTAX	INTEGER
			MAX-ACCESS	read-only
			STATUS	current
			::= { hmWanMbus6C 81 }

hmWanMbus6CVIF26		OBJECT-TYPE
			SYNTAX	INTEGER
			MAX-ACCESS	read-only
			STATUS	current
			::= { hmWanMbus6C 82 }

hmWanMbus6CValue26		OBJECT-TYPE
			SYNTAX	INTEGER
			MAX-ACCESS	read-only
			STATUS	current
			::= { hmWanMbus6C 83 }

hmWanMbus6CVIF27		OBJECT-TYPE
			SYNTAX	INTEGER
			MAX-ACCESS	read-only
			STATUS	current
			::= { hmWanMbus6C 84 }

hmWanMbus6CValue27		OBJECT-TYPE
			SYNTAX	INTEGER
			MAX-ACCESS	read-only
			STATUS	current
			::= { hmWanMbus6C 85 }

hmWanMbus6CVIF28		OBJECT-TYPE
			SYNTAX	INTEGER
			MAX-ACCESS	read-only
			STATUS	current
			::= { hmWanMbus6C 86 }

hmWanMbus6CValue28		OBJECT-TYPE
			SYNTAX	INTEGER
			MAX-ACCESS	read-only
			STATUS	current
			::= { hmWanMbus6C 87 }

hmWanMbus6CVIF29		OBJECT-TYPE
			SYNTAX	INTEGER
			MAX-ACCESS	read-only
			STATUS	current
			::= { hmWanMbus6C 88 }

hmWanMbus6CValue29		OBJECT-TYPE
			SYNTAX	INTEGER
			MAX-ACCESS	read-only
			STATUS	current
			::= { hmWanMbus6C 89 }

hmWanMbus6CVIF2A		OBJECT-TYPE
			SYNTAX	INTEGER
			MAX-ACCESS	read-only
			STATUS	current
			::= { hmWanMbus6C 90 }

hmWanMbus6CValue2A		OBJECT-TYPE
			SYNTAX	INTEGER
			MAX-ACCESS	read-only
			STATUS	current
			::= { hmWanMbus6C 91 }

hmWanMbus6CVIF2B		OBJECT-TYPE
			SYNTAX	INTEGER
			MAX-ACCESS	read-only
			STATUS	current
			::= { hmWanMbus6C 92 }

hmWanMbus6CValue2B		OBJECT-TYPE
			SYNTAX	INTEGER
			MAX-ACCESS	read-only
			STATUS	current
			::= { hmWanMbus6C 93 }

hmWanMbus6CVIF2C		OBJECT-TYPE
			SYNTAX	INTEGER
			MAX-ACCESS	read-only
			STATUS	current
			::= { hmWanMbus6C 94 }

hmWanMbus6CValue2C		OBJECT-TYPE
			SYNTAX	INTEGER
			MAX-ACCESS	read-only
			STATUS	current
			::= { hmWanMbus6C 95 }

hmWanMbus6CVIF2D		OBJECT-TYPE
			SYNTAX	INTEGER
			MAX-ACCESS	read-only
			STATUS	current
			::= { hmWanMbus6C 96 }

hmWanMbus6CValue2D		OBJECT-TYPE
			SYNTAX	INTEGER
			MAX-ACCESS	read-only
			STATUS	current
			::= { hmWanMbus6C 97 }

hmWanMbus6CVIF2E		OBJECT-TYPE
			SYNTAX	INTEGER
			MAX-ACCESS	read-only
			STATUS	current
			::= { hmWanMbus6C 98 }

hmWanMbus6CValue2E		OBJECT-TYPE
			SYNTAX	INTEGER
			MAX-ACCESS	read-only
			STATUS	current
			::= { hmWanMbus6C 99 }

hmWanMbus6CVIF2F		OBJECT-TYPE
			SYNTAX	INTEGER
			MAX-ACCESS	read-only
			STATUS	current
			::= { hmWanMbus6C 100 }

hmWanMbus6CValue2F		OBJECT-TYPE
			SYNTAX	INTEGER
			MAX-ACCESS	read-only
			STATUS	current
			::= { hmWanMbus6C 101 }

hmWanMbus6D			OBJECT IDENTIFIER ::= { hmWanMbus 109 }

hmWanMbus6DIdNumber		OBJECT-TYPE
			SYNTAX	Gauge32
			MAX-ACCESS	read-only
			STATUS	current
			::= { hmWanMbus6D 1 }

hmWanMbus6DManufacturer	OBJECT-TYPE
			SYNTAX	Gauge32
			MAX-ACCESS	read-only
			STATUS	current
			::= { hmWanMbus6D 2 }

hmWanMbus6DVersion		OBJECT-TYPE
			SYNTAX	Gauge32
			MAX-ACCESS	read-only
			STATUS	current
			::= { hmWanMbus6D 3 }

hmWanMbus6DMedium		OBJECT-TYPE
			SYNTAX	Gauge32
			MAX-ACCESS	read-only
			STATUS	current
			::= { hmWanMbus6D 4 }

hmWanMbus6DStatus		OBJECT-TYPE
			SYNTAX	Gauge32
			MAX-ACCESS	read-only
			STATUS	current
			::= { hmWanMbus6D 5 }

hmWanMbus6DVIF00		OBJECT-TYPE
			SYNTAX	INTEGER
			MAX-ACCESS	read-only
			STATUS	current
			::= { hmWanMbus6D 6 }

hmWanMbus6DValue00		OBJECT-TYPE
			SYNTAX	INTEGER
			MAX-ACCESS	read-only
			STATUS	current
			::= { hmWanMbus6D 7 }

hmWanMbus6DVIF01		OBJECT-TYPE
			SYNTAX	INTEGER
			MAX-ACCESS	read-only
			STATUS	current
			::= { hmWanMbus6D 8 }

hmWanMbus6DValue01		OBJECT-TYPE
			SYNTAX	INTEGER
			MAX-ACCESS	read-only
			STATUS	current
			::= { hmWanMbus6D 9 }

hmWanMbus6DVIF02		OBJECT-TYPE
			SYNTAX	INTEGER
			MAX-ACCESS	read-only
			STATUS	current
			::= { hmWanMbus6D 10 }

hmWanMbus6DValue02		OBJECT-TYPE
			SYNTAX	INTEGER
			MAX-ACCESS	read-only
			STATUS	current
			::= { hmWanMbus6D 11 }

hmWanMbus6DVIF03		OBJECT-TYPE
			SYNTAX	INTEGER
			MAX-ACCESS	read-only
			STATUS	current
			::= { hmWanMbus6D 12 }

hmWanMbus6DValue03		OBJECT-TYPE
			SYNTAX	INTEGER
			MAX-ACCESS	read-only
			STATUS	current
			::= { hmWanMbus6D 13 }

hmWanMbus6DVIF04		OBJECT-TYPE
			SYNTAX	INTEGER
			MAX-ACCESS	read-only
			STATUS	current
			::= { hmWanMbus6D 14 }

hmWanMbus6DValue04		OBJECT-TYPE
			SYNTAX	INTEGER
			MAX-ACCESS	read-only
			STATUS	current
			::= { hmWanMbus6D 15 }

hmWanMbus6DVIF05		OBJECT-TYPE
			SYNTAX	INTEGER
			MAX-ACCESS	read-only
			STATUS	current
			::= { hmWanMbus6D 16 }

hmWanMbus6DValue05		OBJECT-TYPE
			SYNTAX	INTEGER
			MAX-ACCESS	read-only
			STATUS	current
			::= { hmWanMbus6D 17 }

hmWanMbus6DVIF06		OBJECT-TYPE
			SYNTAX	INTEGER
			MAX-ACCESS	read-only
			STATUS	current
			::= { hmWanMbus6D 18 }

hmWanMbus6DValue06		OBJECT-TYPE
			SYNTAX	INTEGER
			MAX-ACCESS	read-only
			STATUS	current
			::= { hmWanMbus6D 19 }

hmWanMbus6DVIF07		OBJECT-TYPE
			SYNTAX	INTEGER
			MAX-ACCESS	read-only
			STATUS	current
			::= { hmWanMbus6D 20 }

hmWanMbus6DValue07		OBJECT-TYPE
			SYNTAX	INTEGER
			MAX-ACCESS	read-only
			STATUS	current
			::= { hmWanMbus6D 21 }

hmWanMbus6DVIF08		OBJECT-TYPE
			SYNTAX	INTEGER
			MAX-ACCESS	read-only
			STATUS	current
			::= { hmWanMbus6D 22 }

hmWanMbus6DValue08		OBJECT-TYPE
			SYNTAX	INTEGER
			MAX-ACCESS	read-only
			STATUS	current
			::= { hmWanMbus6D 23 }

hmWanMbus6DVIF09		OBJECT-TYPE
			SYNTAX	INTEGER
			MAX-ACCESS	read-only
			STATUS	current
			::= { hmWanMbus6D 24 }

hmWanMbus6DValue09		OBJECT-TYPE
			SYNTAX	INTEGER
			MAX-ACCESS	read-only
			STATUS	current
			::= { hmWanMbus6D 25 }

hmWanMbus6DVIF0A		OBJECT-TYPE
			SYNTAX	INTEGER
			MAX-ACCESS	read-only
			STATUS	current
			::= { hmWanMbus6D 26 }

hmWanMbus6DValue0A		OBJECT-TYPE
			SYNTAX	INTEGER
			MAX-ACCESS	read-only
			STATUS	current
			::= { hmWanMbus6D 27 }

hmWanMbus6DVIF0B		OBJECT-TYPE
			SYNTAX	INTEGER
			MAX-ACCESS	read-only
			STATUS	current
			::= { hmWanMbus6D 28 }

hmWanMbus6DValue0B		OBJECT-TYPE
			SYNTAX	INTEGER
			MAX-ACCESS	read-only
			STATUS	current
			::= { hmWanMbus6D 29 }

hmWanMbus6DVIF0C		OBJECT-TYPE
			SYNTAX	INTEGER
			MAX-ACCESS	read-only
			STATUS	current
			::= { hmWanMbus6D 30 }

hmWanMbus6DValue0C		OBJECT-TYPE
			SYNTAX	INTEGER
			MAX-ACCESS	read-only
			STATUS	current
			::= { hmWanMbus6D 31 }

hmWanMbus6DVIF0D		OBJECT-TYPE
			SYNTAX	INTEGER
			MAX-ACCESS	read-only
			STATUS	current
			::= { hmWanMbus6D 32 }

hmWanMbus6DValue0D		OBJECT-TYPE
			SYNTAX	INTEGER
			MAX-ACCESS	read-only
			STATUS	current
			::= { hmWanMbus6D 33 }

hmWanMbus6DVIF0E		OBJECT-TYPE
			SYNTAX	INTEGER
			MAX-ACCESS	read-only
			STATUS	current
			::= { hmWanMbus6D 34 }

hmWanMbus6DValue0E		OBJECT-TYPE
			SYNTAX	INTEGER
			MAX-ACCESS	read-only
			STATUS	current
			::= { hmWanMbus6D 35 }

hmWanMbus6DVIF0F		OBJECT-TYPE
			SYNTAX	INTEGER
			MAX-ACCESS	read-only
			STATUS	current
			::= { hmWanMbus6D 36 }

hmWanMbus6DValue0F		OBJECT-TYPE
			SYNTAX	INTEGER
			MAX-ACCESS	read-only
			STATUS	current
			::= { hmWanMbus6D 37 }

hmWanMbus6DVIF10		OBJECT-TYPE
			SYNTAX	INTEGER
			MAX-ACCESS	read-only
			STATUS	current
			::= { hmWanMbus6D 38 }

hmWanMbus6DValue10		OBJECT-TYPE
			SYNTAX	INTEGER
			MAX-ACCESS	read-only
			STATUS	current
			::= { hmWanMbus6D 39 }

hmWanMbus6DVIF11		OBJECT-TYPE
			SYNTAX	INTEGER
			MAX-ACCESS	read-only
			STATUS	current
			::= { hmWanMbus6D 40 }

hmWanMbus6DValue11		OBJECT-TYPE
			SYNTAX	INTEGER
			MAX-ACCESS	read-only
			STATUS	current
			::= { hmWanMbus6D 41 }

hmWanMbus6DVIF12		OBJECT-TYPE
			SYNTAX	INTEGER
			MAX-ACCESS	read-only
			STATUS	current
			::= { hmWanMbus6D 42 }

hmWanMbus6DValue12		OBJECT-TYPE
			SYNTAX	INTEGER
			MAX-ACCESS	read-only
			STATUS	current
			::= { hmWanMbus6D 43 }

hmWanMbus6DVIF13		OBJECT-TYPE
			SYNTAX	INTEGER
			MAX-ACCESS	read-only
			STATUS	current
			::= { hmWanMbus6D 44 }

hmWanMbus6DValue13		OBJECT-TYPE
			SYNTAX	INTEGER
			MAX-ACCESS	read-only
			STATUS	current
			::= { hmWanMbus6D 45 }

hmWanMbus6DVIF14		OBJECT-TYPE
			SYNTAX	INTEGER
			MAX-ACCESS	read-only
			STATUS	current
			::= { hmWanMbus6D 46 }

hmWanMbus6DValue14		OBJECT-TYPE
			SYNTAX	INTEGER
			MAX-ACCESS	read-only
			STATUS	current
			::= { hmWanMbus6D 47 }

hmWanMbus6DVIF15		OBJECT-TYPE
			SYNTAX	INTEGER
			MAX-ACCESS	read-only
			STATUS	current
			::= { hmWanMbus6D 48 }

hmWanMbus6DValue15		OBJECT-TYPE
			SYNTAX	INTEGER
			MAX-ACCESS	read-only
			STATUS	current
			::= { hmWanMbus6D 49 }

hmWanMbus6DVIF16		OBJECT-TYPE
			SYNTAX	INTEGER
			MAX-ACCESS	read-only
			STATUS	current
			::= { hmWanMbus6D 50 }

hmWanMbus6DValue16		OBJECT-TYPE
			SYNTAX	INTEGER
			MAX-ACCESS	read-only
			STATUS	current
			::= { hmWanMbus6D 51 }

hmWanMbus6DVIF17		OBJECT-TYPE
			SYNTAX	INTEGER
			MAX-ACCESS	read-only
			STATUS	current
			::= { hmWanMbus6D 52 }

hmWanMbus6DValue17		OBJECT-TYPE
			SYNTAX	INTEGER
			MAX-ACCESS	read-only
			STATUS	current
			::= { hmWanMbus6D 53 }

hmWanMbus6DVIF18		OBJECT-TYPE
			SYNTAX	INTEGER
			MAX-ACCESS	read-only
			STATUS	current
			::= { hmWanMbus6D 54 }

hmWanMbus6DValue18		OBJECT-TYPE
			SYNTAX	INTEGER
			MAX-ACCESS	read-only
			STATUS	current
			::= { hmWanMbus6D 55 }

hmWanMbus6DVIF19		OBJECT-TYPE
			SYNTAX	INTEGER
			MAX-ACCESS	read-only
			STATUS	current
			::= { hmWanMbus6D 56 }

hmWanMbus6DValue19		OBJECT-TYPE
			SYNTAX	INTEGER
			MAX-ACCESS	read-only
			STATUS	current
			::= { hmWanMbus6D 57 }

hmWanMbus6DVIF1A		OBJECT-TYPE
			SYNTAX	INTEGER
			MAX-ACCESS	read-only
			STATUS	current
			::= { hmWanMbus6D 58 }

hmWanMbus6DValue1A		OBJECT-TYPE
			SYNTAX	INTEGER
			MAX-ACCESS	read-only
			STATUS	current
			::= { hmWanMbus6D 59 }

hmWanMbus6DVIF1B		OBJECT-TYPE
			SYNTAX	INTEGER
			MAX-ACCESS	read-only
			STATUS	current
			::= { hmWanMbus6D 60 }

hmWanMbus6DValue1B		OBJECT-TYPE
			SYNTAX	INTEGER
			MAX-ACCESS	read-only
			STATUS	current
			::= { hmWanMbus6D 61 }

hmWanMbus6DVIF1C		OBJECT-TYPE
			SYNTAX	INTEGER
			MAX-ACCESS	read-only
			STATUS	current
			::= { hmWanMbus6D 62 }

hmWanMbus6DValue1C		OBJECT-TYPE
			SYNTAX	INTEGER
			MAX-ACCESS	read-only
			STATUS	current
			::= { hmWanMbus6D 63 }

hmWanMbus6DVIF1D		OBJECT-TYPE
			SYNTAX	INTEGER
			MAX-ACCESS	read-only
			STATUS	current
			::= { hmWanMbus6D 64 }

hmWanMbus6DValue1D		OBJECT-TYPE
			SYNTAX	INTEGER
			MAX-ACCESS	read-only
			STATUS	current
			::= { hmWanMbus6D 65 }

hmWanMbus6DVIF1E		OBJECT-TYPE
			SYNTAX	INTEGER
			MAX-ACCESS	read-only
			STATUS	current
			::= { hmWanMbus6D 66 }

hmWanMbus6DValue1E		OBJECT-TYPE
			SYNTAX	INTEGER
			MAX-ACCESS	read-only
			STATUS	current
			::= { hmWanMbus6D 67 }

hmWanMbus6DVIF1F		OBJECT-TYPE
			SYNTAX	INTEGER
			MAX-ACCESS	read-only
			STATUS	current
			::= { hmWanMbus6D 68 }

hmWanMbus6DValue1F		OBJECT-TYPE
			SYNTAX	INTEGER
			MAX-ACCESS	read-only
			STATUS	current
			::= { hmWanMbus6D 69 }

hmWanMbus6DVIF20		OBJECT-TYPE
			SYNTAX	INTEGER
			MAX-ACCESS	read-only
			STATUS	current
			::= { hmWanMbus6D 70 }

hmWanMbus6DValue20		OBJECT-TYPE
			SYNTAX	INTEGER
			MAX-ACCESS	read-only
			STATUS	current
			::= { hmWanMbus6D 71 }

hmWanMbus6DVIF21		OBJECT-TYPE
			SYNTAX	INTEGER
			MAX-ACCESS	read-only
			STATUS	current
			::= { hmWanMbus6D 72 }

hmWanMbus6DValue21		OBJECT-TYPE
			SYNTAX	INTEGER
			MAX-ACCESS	read-only
			STATUS	current
			::= { hmWanMbus6D 73 }

hmWanMbus6DVIF22		OBJECT-TYPE
			SYNTAX	INTEGER
			MAX-ACCESS	read-only
			STATUS	current
			::= { hmWanMbus6D 74 }

hmWanMbus6DValue22		OBJECT-TYPE
			SYNTAX	INTEGER
			MAX-ACCESS	read-only
			STATUS	current
			::= { hmWanMbus6D 75 }

hmWanMbus6DVIF23		OBJECT-TYPE
			SYNTAX	INTEGER
			MAX-ACCESS	read-only
			STATUS	current
			::= { hmWanMbus6D 76 }

hmWanMbus6DValue23		OBJECT-TYPE
			SYNTAX	INTEGER
			MAX-ACCESS	read-only
			STATUS	current
			::= { hmWanMbus6D 77 }

hmWanMbus6DVIF24		OBJECT-TYPE
			SYNTAX	INTEGER
			MAX-ACCESS	read-only
			STATUS	current
			::= { hmWanMbus6D 78 }

hmWanMbus6DValue24		OBJECT-TYPE
			SYNTAX	INTEGER
			MAX-ACCESS	read-only
			STATUS	current
			::= { hmWanMbus6D 79 }

hmWanMbus6DVIF25		OBJECT-TYPE
			SYNTAX	INTEGER
			MAX-ACCESS	read-only
			STATUS	current
			::= { hmWanMbus6D 80 }

hmWanMbus6DValue25		OBJECT-TYPE
			SYNTAX	INTEGER
			MAX-ACCESS	read-only
			STATUS	current
			::= { hmWanMbus6D 81 }

hmWanMbus6DVIF26		OBJECT-TYPE
			SYNTAX	INTEGER
			MAX-ACCESS	read-only
			STATUS	current
			::= { hmWanMbus6D 82 }

hmWanMbus6DValue26		OBJECT-TYPE
			SYNTAX	INTEGER
			MAX-ACCESS	read-only
			STATUS	current
			::= { hmWanMbus6D 83 }

hmWanMbus6DVIF27		OBJECT-TYPE
			SYNTAX	INTEGER
			MAX-ACCESS	read-only
			STATUS	current
			::= { hmWanMbus6D 84 }

hmWanMbus6DValue27		OBJECT-TYPE
			SYNTAX	INTEGER
			MAX-ACCESS	read-only
			STATUS	current
			::= { hmWanMbus6D 85 }

hmWanMbus6DVIF28		OBJECT-TYPE
			SYNTAX	INTEGER
			MAX-ACCESS	read-only
			STATUS	current
			::= { hmWanMbus6D 86 }

hmWanMbus6DValue28		OBJECT-TYPE
			SYNTAX	INTEGER
			MAX-ACCESS	read-only
			STATUS	current
			::= { hmWanMbus6D 87 }

hmWanMbus6DVIF29		OBJECT-TYPE
			SYNTAX	INTEGER
			MAX-ACCESS	read-only
			STATUS	current
			::= { hmWanMbus6D 88 }

hmWanMbus6DValue29		OBJECT-TYPE
			SYNTAX	INTEGER
			MAX-ACCESS	read-only
			STATUS	current
			::= { hmWanMbus6D 89 }

hmWanMbus6DVIF2A		OBJECT-TYPE
			SYNTAX	INTEGER
			MAX-ACCESS	read-only
			STATUS	current
			::= { hmWanMbus6D 90 }

hmWanMbus6DValue2A		OBJECT-TYPE
			SYNTAX	INTEGER
			MAX-ACCESS	read-only
			STATUS	current
			::= { hmWanMbus6D 91 }

hmWanMbus6DVIF2B		OBJECT-TYPE
			SYNTAX	INTEGER
			MAX-ACCESS	read-only
			STATUS	current
			::= { hmWanMbus6D 92 }

hmWanMbus6DValue2B		OBJECT-TYPE
			SYNTAX	INTEGER
			MAX-ACCESS	read-only
			STATUS	current
			::= { hmWanMbus6D 93 }

hmWanMbus6DVIF2C		OBJECT-TYPE
			SYNTAX	INTEGER
			MAX-ACCESS	read-only
			STATUS	current
			::= { hmWanMbus6D 94 }

hmWanMbus6DValue2C		OBJECT-TYPE
			SYNTAX	INTEGER
			MAX-ACCESS	read-only
			STATUS	current
			::= { hmWanMbus6D 95 }

hmWanMbus6DVIF2D		OBJECT-TYPE
			SYNTAX	INTEGER
			MAX-ACCESS	read-only
			STATUS	current
			::= { hmWanMbus6D 96 }

hmWanMbus6DValue2D		OBJECT-TYPE
			SYNTAX	INTEGER
			MAX-ACCESS	read-only
			STATUS	current
			::= { hmWanMbus6D 97 }

hmWanMbus6DVIF2E		OBJECT-TYPE
			SYNTAX	INTEGER
			MAX-ACCESS	read-only
			STATUS	current
			::= { hmWanMbus6D 98 }

hmWanMbus6DValue2E		OBJECT-TYPE
			SYNTAX	INTEGER
			MAX-ACCESS	read-only
			STATUS	current
			::= { hmWanMbus6D 99 }

hmWanMbus6DVIF2F		OBJECT-TYPE
			SYNTAX	INTEGER
			MAX-ACCESS	read-only
			STATUS	current
			::= { hmWanMbus6D 100 }

hmWanMbus6DValue2F		OBJECT-TYPE
			SYNTAX	INTEGER
			MAX-ACCESS	read-only
			STATUS	current
			::= { hmWanMbus6D 101 }

hmWanMbus6E			OBJECT IDENTIFIER ::= { hmWanMbus 110 }

hmWanMbus6EIdNumber		OBJECT-TYPE
			SYNTAX	Gauge32
			MAX-ACCESS	read-only
			STATUS	current
			::= { hmWanMbus6E 1 }

hmWanMbus6EManufacturer	OBJECT-TYPE
			SYNTAX	Gauge32
			MAX-ACCESS	read-only
			STATUS	current
			::= { hmWanMbus6E 2 }

hmWanMbus6EVersion		OBJECT-TYPE
			SYNTAX	Gauge32
			MAX-ACCESS	read-only
			STATUS	current
			::= { hmWanMbus6E 3 }

hmWanMbus6EMedium		OBJECT-TYPE
			SYNTAX	Gauge32
			MAX-ACCESS	read-only
			STATUS	current
			::= { hmWanMbus6E 4 }

hmWanMbus6EStatus		OBJECT-TYPE
			SYNTAX	Gauge32
			MAX-ACCESS	read-only
			STATUS	current
			::= { hmWanMbus6E 5 }

hmWanMbus6EVIF00		OBJECT-TYPE
			SYNTAX	INTEGER
			MAX-ACCESS	read-only
			STATUS	current
			::= { hmWanMbus6E 6 }

hmWanMbus6EValue00		OBJECT-TYPE
			SYNTAX	INTEGER
			MAX-ACCESS	read-only
			STATUS	current
			::= { hmWanMbus6E 7 }

hmWanMbus6EVIF01		OBJECT-TYPE
			SYNTAX	INTEGER
			MAX-ACCESS	read-only
			STATUS	current
			::= { hmWanMbus6E 8 }

hmWanMbus6EValue01		OBJECT-TYPE
			SYNTAX	INTEGER
			MAX-ACCESS	read-only
			STATUS	current
			::= { hmWanMbus6E 9 }

hmWanMbus6EVIF02		OBJECT-TYPE
			SYNTAX	INTEGER
			MAX-ACCESS	read-only
			STATUS	current
			::= { hmWanMbus6E 10 }

hmWanMbus6EValue02		OBJECT-TYPE
			SYNTAX	INTEGER
			MAX-ACCESS	read-only
			STATUS	current
			::= { hmWanMbus6E 11 }

hmWanMbus6EVIF03		OBJECT-TYPE
			SYNTAX	INTEGER
			MAX-ACCESS	read-only
			STATUS	current
			::= { hmWanMbus6E 12 }

hmWanMbus6EValue03		OBJECT-TYPE
			SYNTAX	INTEGER
			MAX-ACCESS	read-only
			STATUS	current
			::= { hmWanMbus6E 13 }

hmWanMbus6EVIF04		OBJECT-TYPE
			SYNTAX	INTEGER
			MAX-ACCESS	read-only
			STATUS	current
			::= { hmWanMbus6E 14 }

hmWanMbus6EValue04		OBJECT-TYPE
			SYNTAX	INTEGER
			MAX-ACCESS	read-only
			STATUS	current
			::= { hmWanMbus6E 15 }

hmWanMbus6EVIF05		OBJECT-TYPE
			SYNTAX	INTEGER
			MAX-ACCESS	read-only
			STATUS	current
			::= { hmWanMbus6E 16 }

hmWanMbus6EValue05		OBJECT-TYPE
			SYNTAX	INTEGER
			MAX-ACCESS	read-only
			STATUS	current
			::= { hmWanMbus6E 17 }

hmWanMbus6EVIF06		OBJECT-TYPE
			SYNTAX	INTEGER
			MAX-ACCESS	read-only
			STATUS	current
			::= { hmWanMbus6E 18 }

hmWanMbus6EValue06		OBJECT-TYPE
			SYNTAX	INTEGER
			MAX-ACCESS	read-only
			STATUS	current
			::= { hmWanMbus6E 19 }

hmWanMbus6EVIF07		OBJECT-TYPE
			SYNTAX	INTEGER
			MAX-ACCESS	read-only
			STATUS	current
			::= { hmWanMbus6E 20 }

hmWanMbus6EValue07		OBJECT-TYPE
			SYNTAX	INTEGER
			MAX-ACCESS	read-only
			STATUS	current
			::= { hmWanMbus6E 21 }

hmWanMbus6EVIF08		OBJECT-TYPE
			SYNTAX	INTEGER
			MAX-ACCESS	read-only
			STATUS	current
			::= { hmWanMbus6E 22 }

hmWanMbus6EValue08		OBJECT-TYPE
			SYNTAX	INTEGER
			MAX-ACCESS	read-only
			STATUS	current
			::= { hmWanMbus6E 23 }

hmWanMbus6EVIF09		OBJECT-TYPE
			SYNTAX	INTEGER
			MAX-ACCESS	read-only
			STATUS	current
			::= { hmWanMbus6E 24 }

hmWanMbus6EValue09		OBJECT-TYPE
			SYNTAX	INTEGER
			MAX-ACCESS	read-only
			STATUS	current
			::= { hmWanMbus6E 25 }

hmWanMbus6EVIF0A		OBJECT-TYPE
			SYNTAX	INTEGER
			MAX-ACCESS	read-only
			STATUS	current
			::= { hmWanMbus6E 26 }

hmWanMbus6EValue0A		OBJECT-TYPE
			SYNTAX	INTEGER
			MAX-ACCESS	read-only
			STATUS	current
			::= { hmWanMbus6E 27 }

hmWanMbus6EVIF0B		OBJECT-TYPE
			SYNTAX	INTEGER
			MAX-ACCESS	read-only
			STATUS	current
			::= { hmWanMbus6E 28 }

hmWanMbus6EValue0B		OBJECT-TYPE
			SYNTAX	INTEGER
			MAX-ACCESS	read-only
			STATUS	current
			::= { hmWanMbus6E 29 }

hmWanMbus6EVIF0C		OBJECT-TYPE
			SYNTAX	INTEGER
			MAX-ACCESS	read-only
			STATUS	current
			::= { hmWanMbus6E 30 }

hmWanMbus6EValue0C		OBJECT-TYPE
			SYNTAX	INTEGER
			MAX-ACCESS	read-only
			STATUS	current
			::= { hmWanMbus6E 31 }

hmWanMbus6EVIF0D		OBJECT-TYPE
			SYNTAX	INTEGER
			MAX-ACCESS	read-only
			STATUS	current
			::= { hmWanMbus6E 32 }

hmWanMbus6EValue0D		OBJECT-TYPE
			SYNTAX	INTEGER
			MAX-ACCESS	read-only
			STATUS	current
			::= { hmWanMbus6E 33 }

hmWanMbus6EVIF0E		OBJECT-TYPE
			SYNTAX	INTEGER
			MAX-ACCESS	read-only
			STATUS	current
			::= { hmWanMbus6E 34 }

hmWanMbus6EValue0E		OBJECT-TYPE
			SYNTAX	INTEGER
			MAX-ACCESS	read-only
			STATUS	current
			::= { hmWanMbus6E 35 }

hmWanMbus6EVIF0F		OBJECT-TYPE
			SYNTAX	INTEGER
			MAX-ACCESS	read-only
			STATUS	current
			::= { hmWanMbus6E 36 }

hmWanMbus6EValue0F		OBJECT-TYPE
			SYNTAX	INTEGER
			MAX-ACCESS	read-only
			STATUS	current
			::= { hmWanMbus6E 37 }

hmWanMbus6EVIF10		OBJECT-TYPE
			SYNTAX	INTEGER
			MAX-ACCESS	read-only
			STATUS	current
			::= { hmWanMbus6E 38 }

hmWanMbus6EValue10		OBJECT-TYPE
			SYNTAX	INTEGER
			MAX-ACCESS	read-only
			STATUS	current
			::= { hmWanMbus6E 39 }

hmWanMbus6EVIF11		OBJECT-TYPE
			SYNTAX	INTEGER
			MAX-ACCESS	read-only
			STATUS	current
			::= { hmWanMbus6E 40 }

hmWanMbus6EValue11		OBJECT-TYPE
			SYNTAX	INTEGER
			MAX-ACCESS	read-only
			STATUS	current
			::= { hmWanMbus6E 41 }

hmWanMbus6EVIF12		OBJECT-TYPE
			SYNTAX	INTEGER
			MAX-ACCESS	read-only
			STATUS	current
			::= { hmWanMbus6E 42 }

hmWanMbus6EValue12		OBJECT-TYPE
			SYNTAX	INTEGER
			MAX-ACCESS	read-only
			STATUS	current
			::= { hmWanMbus6E 43 }

hmWanMbus6EVIF13		OBJECT-TYPE
			SYNTAX	INTEGER
			MAX-ACCESS	read-only
			STATUS	current
			::= { hmWanMbus6E 44 }

hmWanMbus6EValue13		OBJECT-TYPE
			SYNTAX	INTEGER
			MAX-ACCESS	read-only
			STATUS	current
			::= { hmWanMbus6E 45 }

hmWanMbus6EVIF14		OBJECT-TYPE
			SYNTAX	INTEGER
			MAX-ACCESS	read-only
			STATUS	current
			::= { hmWanMbus6E 46 }

hmWanMbus6EValue14		OBJECT-TYPE
			SYNTAX	INTEGER
			MAX-ACCESS	read-only
			STATUS	current
			::= { hmWanMbus6E 47 }

hmWanMbus6EVIF15		OBJECT-TYPE
			SYNTAX	INTEGER
			MAX-ACCESS	read-only
			STATUS	current
			::= { hmWanMbus6E 48 }

hmWanMbus6EValue15		OBJECT-TYPE
			SYNTAX	INTEGER
			MAX-ACCESS	read-only
			STATUS	current
			::= { hmWanMbus6E 49 }

hmWanMbus6EVIF16		OBJECT-TYPE
			SYNTAX	INTEGER
			MAX-ACCESS	read-only
			STATUS	current
			::= { hmWanMbus6E 50 }

hmWanMbus6EValue16		OBJECT-TYPE
			SYNTAX	INTEGER
			MAX-ACCESS	read-only
			STATUS	current
			::= { hmWanMbus6E 51 }

hmWanMbus6EVIF17		OBJECT-TYPE
			SYNTAX	INTEGER
			MAX-ACCESS	read-only
			STATUS	current
			::= { hmWanMbus6E 52 }

hmWanMbus6EValue17		OBJECT-TYPE
			SYNTAX	INTEGER
			MAX-ACCESS	read-only
			STATUS	current
			::= { hmWanMbus6E 53 }

hmWanMbus6EVIF18		OBJECT-TYPE
			SYNTAX	INTEGER
			MAX-ACCESS	read-only
			STATUS	current
			::= { hmWanMbus6E 54 }

hmWanMbus6EValue18		OBJECT-TYPE
			SYNTAX	INTEGER
			MAX-ACCESS	read-only
			STATUS	current
			::= { hmWanMbus6E 55 }

hmWanMbus6EVIF19		OBJECT-TYPE
			SYNTAX	INTEGER
			MAX-ACCESS	read-only
			STATUS	current
			::= { hmWanMbus6E 56 }

hmWanMbus6EValue19		OBJECT-TYPE
			SYNTAX	INTEGER
			MAX-ACCESS	read-only
			STATUS	current
			::= { hmWanMbus6E 57 }

hmWanMbus6EVIF1A		OBJECT-TYPE
			SYNTAX	INTEGER
			MAX-ACCESS	read-only
			STATUS	current
			::= { hmWanMbus6E 58 }

hmWanMbus6EValue1A		OBJECT-TYPE
			SYNTAX	INTEGER
			MAX-ACCESS	read-only
			STATUS	current
			::= { hmWanMbus6E 59 }

hmWanMbus6EVIF1B		OBJECT-TYPE
			SYNTAX	INTEGER
			MAX-ACCESS	read-only
			STATUS	current
			::= { hmWanMbus6E 60 }

hmWanMbus6EValue1B		OBJECT-TYPE
			SYNTAX	INTEGER
			MAX-ACCESS	read-only
			STATUS	current
			::= { hmWanMbus6E 61 }

hmWanMbus6EVIF1C		OBJECT-TYPE
			SYNTAX	INTEGER
			MAX-ACCESS	read-only
			STATUS	current
			::= { hmWanMbus6E 62 }

hmWanMbus6EValue1C		OBJECT-TYPE
			SYNTAX	INTEGER
			MAX-ACCESS	read-only
			STATUS	current
			::= { hmWanMbus6E 63 }

hmWanMbus6EVIF1D		OBJECT-TYPE
			SYNTAX	INTEGER
			MAX-ACCESS	read-only
			STATUS	current
			::= { hmWanMbus6E 64 }

hmWanMbus6EValue1D		OBJECT-TYPE
			SYNTAX	INTEGER
			MAX-ACCESS	read-only
			STATUS	current
			::= { hmWanMbus6E 65 }

hmWanMbus6EVIF1E		OBJECT-TYPE
			SYNTAX	INTEGER
			MAX-ACCESS	read-only
			STATUS	current
			::= { hmWanMbus6E 66 }

hmWanMbus6EValue1E		OBJECT-TYPE
			SYNTAX	INTEGER
			MAX-ACCESS	read-only
			STATUS	current
			::= { hmWanMbus6E 67 }

hmWanMbus6EVIF1F		OBJECT-TYPE
			SYNTAX	INTEGER
			MAX-ACCESS	read-only
			STATUS	current
			::= { hmWanMbus6E 68 }

hmWanMbus6EValue1F		OBJECT-TYPE
			SYNTAX	INTEGER
			MAX-ACCESS	read-only
			STATUS	current
			::= { hmWanMbus6E 69 }

hmWanMbus6EVIF20		OBJECT-TYPE
			SYNTAX	INTEGER
			MAX-ACCESS	read-only
			STATUS	current
			::= { hmWanMbus6E 70 }

hmWanMbus6EValue20		OBJECT-TYPE
			SYNTAX	INTEGER
			MAX-ACCESS	read-only
			STATUS	current
			::= { hmWanMbus6E 71 }

hmWanMbus6EVIF21		OBJECT-TYPE
			SYNTAX	INTEGER
			MAX-ACCESS	read-only
			STATUS	current
			::= { hmWanMbus6E 72 }

hmWanMbus6EValue21		OBJECT-TYPE
			SYNTAX	INTEGER
			MAX-ACCESS	read-only
			STATUS	current
			::= { hmWanMbus6E 73 }

hmWanMbus6EVIF22		OBJECT-TYPE
			SYNTAX	INTEGER
			MAX-ACCESS	read-only
			STATUS	current
			::= { hmWanMbus6E 74 }

hmWanMbus6EValue22		OBJECT-TYPE
			SYNTAX	INTEGER
			MAX-ACCESS	read-only
			STATUS	current
			::= { hmWanMbus6E 75 }

hmWanMbus6EVIF23		OBJECT-TYPE
			SYNTAX	INTEGER
			MAX-ACCESS	read-only
			STATUS	current
			::= { hmWanMbus6E 76 }

hmWanMbus6EValue23		OBJECT-TYPE
			SYNTAX	INTEGER
			MAX-ACCESS	read-only
			STATUS	current
			::= { hmWanMbus6E 77 }

hmWanMbus6EVIF24		OBJECT-TYPE
			SYNTAX	INTEGER
			MAX-ACCESS	read-only
			STATUS	current
			::= { hmWanMbus6E 78 }

hmWanMbus6EValue24		OBJECT-TYPE
			SYNTAX	INTEGER
			MAX-ACCESS	read-only
			STATUS	current
			::= { hmWanMbus6E 79 }

hmWanMbus6EVIF25		OBJECT-TYPE
			SYNTAX	INTEGER
			MAX-ACCESS	read-only
			STATUS	current
			::= { hmWanMbus6E 80 }

hmWanMbus6EValue25		OBJECT-TYPE
			SYNTAX	INTEGER
			MAX-ACCESS	read-only
			STATUS	current
			::= { hmWanMbus6E 81 }

hmWanMbus6EVIF26		OBJECT-TYPE
			SYNTAX	INTEGER
			MAX-ACCESS	read-only
			STATUS	current
			::= { hmWanMbus6E 82 }

hmWanMbus6EValue26		OBJECT-TYPE
			SYNTAX	INTEGER
			MAX-ACCESS	read-only
			STATUS	current
			::= { hmWanMbus6E 83 }

hmWanMbus6EVIF27		OBJECT-TYPE
			SYNTAX	INTEGER
			MAX-ACCESS	read-only
			STATUS	current
			::= { hmWanMbus6E 84 }

hmWanMbus6EValue27		OBJECT-TYPE
			SYNTAX	INTEGER
			MAX-ACCESS	read-only
			STATUS	current
			::= { hmWanMbus6E 85 }

hmWanMbus6EVIF28		OBJECT-TYPE
			SYNTAX	INTEGER
			MAX-ACCESS	read-only
			STATUS	current
			::= { hmWanMbus6E 86 }

hmWanMbus6EValue28		OBJECT-TYPE
			SYNTAX	INTEGER
			MAX-ACCESS	read-only
			STATUS	current
			::= { hmWanMbus6E 87 }

hmWanMbus6EVIF29		OBJECT-TYPE
			SYNTAX	INTEGER
			MAX-ACCESS	read-only
			STATUS	current
			::= { hmWanMbus6E 88 }

hmWanMbus6EValue29		OBJECT-TYPE
			SYNTAX	INTEGER
			MAX-ACCESS	read-only
			STATUS	current
			::= { hmWanMbus6E 89 }

hmWanMbus6EVIF2A		OBJECT-TYPE
			SYNTAX	INTEGER
			MAX-ACCESS	read-only
			STATUS	current
			::= { hmWanMbus6E 90 }

hmWanMbus6EValue2A		OBJECT-TYPE
			SYNTAX	INTEGER
			MAX-ACCESS	read-only
			STATUS	current
			::= { hmWanMbus6E 91 }

hmWanMbus6EVIF2B		OBJECT-TYPE
			SYNTAX	INTEGER
			MAX-ACCESS	read-only
			STATUS	current
			::= { hmWanMbus6E 92 }

hmWanMbus6EValue2B		OBJECT-TYPE
			SYNTAX	INTEGER
			MAX-ACCESS	read-only
			STATUS	current
			::= { hmWanMbus6E 93 }

hmWanMbus6EVIF2C		OBJECT-TYPE
			SYNTAX	INTEGER
			MAX-ACCESS	read-only
			STATUS	current
			::= { hmWanMbus6E 94 }

hmWanMbus6EValue2C		OBJECT-TYPE
			SYNTAX	INTEGER
			MAX-ACCESS	read-only
			STATUS	current
			::= { hmWanMbus6E 95 }

hmWanMbus6EVIF2D		OBJECT-TYPE
			SYNTAX	INTEGER
			MAX-ACCESS	read-only
			STATUS	current
			::= { hmWanMbus6E 96 }

hmWanMbus6EValue2D		OBJECT-TYPE
			SYNTAX	INTEGER
			MAX-ACCESS	read-only
			STATUS	current
			::= { hmWanMbus6E 97 }

hmWanMbus6EVIF2E		OBJECT-TYPE
			SYNTAX	INTEGER
			MAX-ACCESS	read-only
			STATUS	current
			::= { hmWanMbus6E 98 }

hmWanMbus6EValue2E		OBJECT-TYPE
			SYNTAX	INTEGER
			MAX-ACCESS	read-only
			STATUS	current
			::= { hmWanMbus6E 99 }

hmWanMbus6EVIF2F		OBJECT-TYPE
			SYNTAX	INTEGER
			MAX-ACCESS	read-only
			STATUS	current
			::= { hmWanMbus6E 100 }

hmWanMbus6EValue2F		OBJECT-TYPE
			SYNTAX	INTEGER
			MAX-ACCESS	read-only
			STATUS	current
			::= { hmWanMbus6E 101 }

hmWanMbus6F			OBJECT IDENTIFIER ::= { hmWanMbus 111 }

hmWanMbus6FIdNumber		OBJECT-TYPE
			SYNTAX	Gauge32
			MAX-ACCESS	read-only
			STATUS	current
			::= { hmWanMbus6F 1 }

hmWanMbus6FManufacturer	OBJECT-TYPE
			SYNTAX	Gauge32
			MAX-ACCESS	read-only
			STATUS	current
			::= { hmWanMbus6F 2 }

hmWanMbus6FVersion		OBJECT-TYPE
			SYNTAX	Gauge32
			MAX-ACCESS	read-only
			STATUS	current
			::= { hmWanMbus6F 3 }

hmWanMbus6FMedium		OBJECT-TYPE
			SYNTAX	Gauge32
			MAX-ACCESS	read-only
			STATUS	current
			::= { hmWanMbus6F 4 }

hmWanMbus6FStatus		OBJECT-TYPE
			SYNTAX	Gauge32
			MAX-ACCESS	read-only
			STATUS	current
			::= { hmWanMbus6F 5 }

hmWanMbus6FVIF00		OBJECT-TYPE
			SYNTAX	INTEGER
			MAX-ACCESS	read-only
			STATUS	current
			::= { hmWanMbus6F 6 }

hmWanMbus6FValue00		OBJECT-TYPE
			SYNTAX	INTEGER
			MAX-ACCESS	read-only
			STATUS	current
			::= { hmWanMbus6F 7 }

hmWanMbus6FVIF01		OBJECT-TYPE
			SYNTAX	INTEGER
			MAX-ACCESS	read-only
			STATUS	current
			::= { hmWanMbus6F 8 }

hmWanMbus6FValue01		OBJECT-TYPE
			SYNTAX	INTEGER
			MAX-ACCESS	read-only
			STATUS	current
			::= { hmWanMbus6F 9 }

hmWanMbus6FVIF02		OBJECT-TYPE
			SYNTAX	INTEGER
			MAX-ACCESS	read-only
			STATUS	current
			::= { hmWanMbus6F 10 }

hmWanMbus6FValue02		OBJECT-TYPE
			SYNTAX	INTEGER
			MAX-ACCESS	read-only
			STATUS	current
			::= { hmWanMbus6F 11 }

hmWanMbus6FVIF03		OBJECT-TYPE
			SYNTAX	INTEGER
			MAX-ACCESS	read-only
			STATUS	current
			::= { hmWanMbus6F 12 }

hmWanMbus6FValue03		OBJECT-TYPE
			SYNTAX	INTEGER
			MAX-ACCESS	read-only
			STATUS	current
			::= { hmWanMbus6F 13 }

hmWanMbus6FVIF04		OBJECT-TYPE
			SYNTAX	INTEGER
			MAX-ACCESS	read-only
			STATUS	current
			::= { hmWanMbus6F 14 }

hmWanMbus6FValue04		OBJECT-TYPE
			SYNTAX	INTEGER
			MAX-ACCESS	read-only
			STATUS	current
			::= { hmWanMbus6F 15 }

hmWanMbus6FVIF05		OBJECT-TYPE
			SYNTAX	INTEGER
			MAX-ACCESS	read-only
			STATUS	current
			::= { hmWanMbus6F 16 }

hmWanMbus6FValue05		OBJECT-TYPE
			SYNTAX	INTEGER
			MAX-ACCESS	read-only
			STATUS	current
			::= { hmWanMbus6F 17 }

hmWanMbus6FVIF06		OBJECT-TYPE
			SYNTAX	INTEGER
			MAX-ACCESS	read-only
			STATUS	current
			::= { hmWanMbus6F 18 }

hmWanMbus6FValue06		OBJECT-TYPE
			SYNTAX	INTEGER
			MAX-ACCESS	read-only
			STATUS	current
			::= { hmWanMbus6F 19 }

hmWanMbus6FVIF07		OBJECT-TYPE
			SYNTAX	INTEGER
			MAX-ACCESS	read-only
			STATUS	current
			::= { hmWanMbus6F 20 }

hmWanMbus6FValue07		OBJECT-TYPE
			SYNTAX	INTEGER
			MAX-ACCESS	read-only
			STATUS	current
			::= { hmWanMbus6F 21 }

hmWanMbus6FVIF08		OBJECT-TYPE
			SYNTAX	INTEGER
			MAX-ACCESS	read-only
			STATUS	current
			::= { hmWanMbus6F 22 }

hmWanMbus6FValue08		OBJECT-TYPE
			SYNTAX	INTEGER
			MAX-ACCESS	read-only
			STATUS	current
			::= { hmWanMbus6F 23 }

hmWanMbus6FVIF09		OBJECT-TYPE
			SYNTAX	INTEGER
			MAX-ACCESS	read-only
			STATUS	current
			::= { hmWanMbus6F 24 }

hmWanMbus6FValue09		OBJECT-TYPE
			SYNTAX	INTEGER
			MAX-ACCESS	read-only
			STATUS	current
			::= { hmWanMbus6F 25 }

hmWanMbus6FVIF0A		OBJECT-TYPE
			SYNTAX	INTEGER
			MAX-ACCESS	read-only
			STATUS	current
			::= { hmWanMbus6F 26 }

hmWanMbus6FValue0A		OBJECT-TYPE
			SYNTAX	INTEGER
			MAX-ACCESS	read-only
			STATUS	current
			::= { hmWanMbus6F 27 }

hmWanMbus6FVIF0B		OBJECT-TYPE
			SYNTAX	INTEGER
			MAX-ACCESS	read-only
			STATUS	current
			::= { hmWanMbus6F 28 }

hmWanMbus6FValue0B		OBJECT-TYPE
			SYNTAX	INTEGER
			MAX-ACCESS	read-only
			STATUS	current
			::= { hmWanMbus6F 29 }

hmWanMbus6FVIF0C		OBJECT-TYPE
			SYNTAX	INTEGER
			MAX-ACCESS	read-only
			STATUS	current
			::= { hmWanMbus6F 30 }

hmWanMbus6FValue0C		OBJECT-TYPE
			SYNTAX	INTEGER
			MAX-ACCESS	read-only
			STATUS	current
			::= { hmWanMbus6F 31 }

hmWanMbus6FVIF0D		OBJECT-TYPE
			SYNTAX	INTEGER
			MAX-ACCESS	read-only
			STATUS	current
			::= { hmWanMbus6F 32 }

hmWanMbus6FValue0D		OBJECT-TYPE
			SYNTAX	INTEGER
			MAX-ACCESS	read-only
			STATUS	current
			::= { hmWanMbus6F 33 }

hmWanMbus6FVIF0E		OBJECT-TYPE
			SYNTAX	INTEGER
			MAX-ACCESS	read-only
			STATUS	current
			::= { hmWanMbus6F 34 }

hmWanMbus6FValue0E		OBJECT-TYPE
			SYNTAX	INTEGER
			MAX-ACCESS	read-only
			STATUS	current
			::= { hmWanMbus6F 35 }

hmWanMbus6FVIF0F		OBJECT-TYPE
			SYNTAX	INTEGER
			MAX-ACCESS	read-only
			STATUS	current
			::= { hmWanMbus6F 36 }

hmWanMbus6FValue0F		OBJECT-TYPE
			SYNTAX	INTEGER
			MAX-ACCESS	read-only
			STATUS	current
			::= { hmWanMbus6F 37 }

hmWanMbus6FVIF10		OBJECT-TYPE
			SYNTAX	INTEGER
			MAX-ACCESS	read-only
			STATUS	current
			::= { hmWanMbus6F 38 }

hmWanMbus6FValue10		OBJECT-TYPE
			SYNTAX	INTEGER
			MAX-ACCESS	read-only
			STATUS	current
			::= { hmWanMbus6F 39 }

hmWanMbus6FVIF11		OBJECT-TYPE
			SYNTAX	INTEGER
			MAX-ACCESS	read-only
			STATUS	current
			::= { hmWanMbus6F 40 }

hmWanMbus6FValue11		OBJECT-TYPE
			SYNTAX	INTEGER
			MAX-ACCESS	read-only
			STATUS	current
			::= { hmWanMbus6F 41 }

hmWanMbus6FVIF12		OBJECT-TYPE
			SYNTAX	INTEGER
			MAX-ACCESS	read-only
			STATUS	current
			::= { hmWanMbus6F 42 }

hmWanMbus6FValue12		OBJECT-TYPE
			SYNTAX	INTEGER
			MAX-ACCESS	read-only
			STATUS	current
			::= { hmWanMbus6F 43 }

hmWanMbus6FVIF13		OBJECT-TYPE
			SYNTAX	INTEGER
			MAX-ACCESS	read-only
			STATUS	current
			::= { hmWanMbus6F 44 }

hmWanMbus6FValue13		OBJECT-TYPE
			SYNTAX	INTEGER
			MAX-ACCESS	read-only
			STATUS	current
			::= { hmWanMbus6F 45 }

hmWanMbus6FVIF14		OBJECT-TYPE
			SYNTAX	INTEGER
			MAX-ACCESS	read-only
			STATUS	current
			::= { hmWanMbus6F 46 }

hmWanMbus6FValue14		OBJECT-TYPE
			SYNTAX	INTEGER
			MAX-ACCESS	read-only
			STATUS	current
			::= { hmWanMbus6F 47 }

hmWanMbus6FVIF15		OBJECT-TYPE
			SYNTAX	INTEGER
			MAX-ACCESS	read-only
			STATUS	current
			::= { hmWanMbus6F 48 }

hmWanMbus6FValue15		OBJECT-TYPE
			SYNTAX	INTEGER
			MAX-ACCESS	read-only
			STATUS	current
			::= { hmWanMbus6F 49 }

hmWanMbus6FVIF16		OBJECT-TYPE
			SYNTAX	INTEGER
			MAX-ACCESS	read-only
			STATUS	current
			::= { hmWanMbus6F 50 }

hmWanMbus6FValue16		OBJECT-TYPE
			SYNTAX	INTEGER
			MAX-ACCESS	read-only
			STATUS	current
			::= { hmWanMbus6F 51 }

hmWanMbus6FVIF17		OBJECT-TYPE
			SYNTAX	INTEGER
			MAX-ACCESS	read-only
			STATUS	current
			::= { hmWanMbus6F 52 }

hmWanMbus6FValue17		OBJECT-TYPE
			SYNTAX	INTEGER
			MAX-ACCESS	read-only
			STATUS	current
			::= { hmWanMbus6F 53 }

hmWanMbus6FVIF18		OBJECT-TYPE
			SYNTAX	INTEGER
			MAX-ACCESS	read-only
			STATUS	current
			::= { hmWanMbus6F 54 }

hmWanMbus6FValue18		OBJECT-TYPE
			SYNTAX	INTEGER
			MAX-ACCESS	read-only
			STATUS	current
			::= { hmWanMbus6F 55 }

hmWanMbus6FVIF19		OBJECT-TYPE
			SYNTAX	INTEGER
			MAX-ACCESS	read-only
			STATUS	current
			::= { hmWanMbus6F 56 }

hmWanMbus6FValue19		OBJECT-TYPE
			SYNTAX	INTEGER
			MAX-ACCESS	read-only
			STATUS	current
			::= { hmWanMbus6F 57 }

hmWanMbus6FVIF1A		OBJECT-TYPE
			SYNTAX	INTEGER
			MAX-ACCESS	read-only
			STATUS	current
			::= { hmWanMbus6F 58 }

hmWanMbus6FValue1A		OBJECT-TYPE
			SYNTAX	INTEGER
			MAX-ACCESS	read-only
			STATUS	current
			::= { hmWanMbus6F 59 }

hmWanMbus6FVIF1B		OBJECT-TYPE
			SYNTAX	INTEGER
			MAX-ACCESS	read-only
			STATUS	current
			::= { hmWanMbus6F 60 }

hmWanMbus6FValue1B		OBJECT-TYPE
			SYNTAX	INTEGER
			MAX-ACCESS	read-only
			STATUS	current
			::= { hmWanMbus6F 61 }

hmWanMbus6FVIF1C		OBJECT-TYPE
			SYNTAX	INTEGER
			MAX-ACCESS	read-only
			STATUS	current
			::= { hmWanMbus6F 62 }

hmWanMbus6FValue1C		OBJECT-TYPE
			SYNTAX	INTEGER
			MAX-ACCESS	read-only
			STATUS	current
			::= { hmWanMbus6F 63 }

hmWanMbus6FVIF1D		OBJECT-TYPE
			SYNTAX	INTEGER
			MAX-ACCESS	read-only
			STATUS	current
			::= { hmWanMbus6F 64 }

hmWanMbus6FValue1D		OBJECT-TYPE
			SYNTAX	INTEGER
			MAX-ACCESS	read-only
			STATUS	current
			::= { hmWanMbus6F 65 }

hmWanMbus6FVIF1E		OBJECT-TYPE
			SYNTAX	INTEGER
			MAX-ACCESS	read-only
			STATUS	current
			::= { hmWanMbus6F 66 }

hmWanMbus6FValue1E		OBJECT-TYPE
			SYNTAX	INTEGER
			MAX-ACCESS	read-only
			STATUS	current
			::= { hmWanMbus6F 67 }

hmWanMbus6FVIF1F		OBJECT-TYPE
			SYNTAX	INTEGER
			MAX-ACCESS	read-only
			STATUS	current
			::= { hmWanMbus6F 68 }

hmWanMbus6FValue1F		OBJECT-TYPE
			SYNTAX	INTEGER
			MAX-ACCESS	read-only
			STATUS	current
			::= { hmWanMbus6F 69 }

hmWanMbus6FVIF20		OBJECT-TYPE
			SYNTAX	INTEGER
			MAX-ACCESS	read-only
			STATUS	current
			::= { hmWanMbus6F 70 }

hmWanMbus6FValue20		OBJECT-TYPE
			SYNTAX	INTEGER
			MAX-ACCESS	read-only
			STATUS	current
			::= { hmWanMbus6F 71 }

hmWanMbus6FVIF21		OBJECT-TYPE
			SYNTAX	INTEGER
			MAX-ACCESS	read-only
			STATUS	current
			::= { hmWanMbus6F 72 }

hmWanMbus6FValue21		OBJECT-TYPE
			SYNTAX	INTEGER
			MAX-ACCESS	read-only
			STATUS	current
			::= { hmWanMbus6F 73 }

hmWanMbus6FVIF22		OBJECT-TYPE
			SYNTAX	INTEGER
			MAX-ACCESS	read-only
			STATUS	current
			::= { hmWanMbus6F 74 }

hmWanMbus6FValue22		OBJECT-TYPE
			SYNTAX	INTEGER
			MAX-ACCESS	read-only
			STATUS	current
			::= { hmWanMbus6F 75 }

hmWanMbus6FVIF23		OBJECT-TYPE
			SYNTAX	INTEGER
			MAX-ACCESS	read-only
			STATUS	current
			::= { hmWanMbus6F 76 }

hmWanMbus6FValue23		OBJECT-TYPE
			SYNTAX	INTEGER
			MAX-ACCESS	read-only
			STATUS	current
			::= { hmWanMbus6F 77 }

hmWanMbus6FVIF24		OBJECT-TYPE
			SYNTAX	INTEGER
			MAX-ACCESS	read-only
			STATUS	current
			::= { hmWanMbus6F 78 }

hmWanMbus6FValue24		OBJECT-TYPE
			SYNTAX	INTEGER
			MAX-ACCESS	read-only
			STATUS	current
			::= { hmWanMbus6F 79 }

hmWanMbus6FVIF25		OBJECT-TYPE
			SYNTAX	INTEGER
			MAX-ACCESS	read-only
			STATUS	current
			::= { hmWanMbus6F 80 }

hmWanMbus6FValue25		OBJECT-TYPE
			SYNTAX	INTEGER
			MAX-ACCESS	read-only
			STATUS	current
			::= { hmWanMbus6F 81 }

hmWanMbus6FVIF26		OBJECT-TYPE
			SYNTAX	INTEGER
			MAX-ACCESS	read-only
			STATUS	current
			::= { hmWanMbus6F 82 }

hmWanMbus6FValue26		OBJECT-TYPE
			SYNTAX	INTEGER
			MAX-ACCESS	read-only
			STATUS	current
			::= { hmWanMbus6F 83 }

hmWanMbus6FVIF27		OBJECT-TYPE
			SYNTAX	INTEGER
			MAX-ACCESS	read-only
			STATUS	current
			::= { hmWanMbus6F 84 }

hmWanMbus6FValue27		OBJECT-TYPE
			SYNTAX	INTEGER
			MAX-ACCESS	read-only
			STATUS	current
			::= { hmWanMbus6F 85 }

hmWanMbus6FVIF28		OBJECT-TYPE
			SYNTAX	INTEGER
			MAX-ACCESS	read-only
			STATUS	current
			::= { hmWanMbus6F 86 }

hmWanMbus6FValue28		OBJECT-TYPE
			SYNTAX	INTEGER
			MAX-ACCESS	read-only
			STATUS	current
			::= { hmWanMbus6F 87 }

hmWanMbus6FVIF29		OBJECT-TYPE
			SYNTAX	INTEGER
			MAX-ACCESS	read-only
			STATUS	current
			::= { hmWanMbus6F 88 }

hmWanMbus6FValue29		OBJECT-TYPE
			SYNTAX	INTEGER
			MAX-ACCESS	read-only
			STATUS	current
			::= { hmWanMbus6F 89 }

hmWanMbus6FVIF2A		OBJECT-TYPE
			SYNTAX	INTEGER
			MAX-ACCESS	read-only
			STATUS	current
			::= { hmWanMbus6F 90 }

hmWanMbus6FValue2A		OBJECT-TYPE
			SYNTAX	INTEGER
			MAX-ACCESS	read-only
			STATUS	current
			::= { hmWanMbus6F 91 }

hmWanMbus6FVIF2B		OBJECT-TYPE
			SYNTAX	INTEGER
			MAX-ACCESS	read-only
			STATUS	current
			::= { hmWanMbus6F 92 }

hmWanMbus6FValue2B		OBJECT-TYPE
			SYNTAX	INTEGER
			MAX-ACCESS	read-only
			STATUS	current
			::= { hmWanMbus6F 93 }

hmWanMbus6FVIF2C		OBJECT-TYPE
			SYNTAX	INTEGER
			MAX-ACCESS	read-only
			STATUS	current
			::= { hmWanMbus6F 94 }

hmWanMbus6FValue2C		OBJECT-TYPE
			SYNTAX	INTEGER
			MAX-ACCESS	read-only
			STATUS	current
			::= { hmWanMbus6F 95 }

hmWanMbus6FVIF2D		OBJECT-TYPE
			SYNTAX	INTEGER
			MAX-ACCESS	read-only
			STATUS	current
			::= { hmWanMbus6F 96 }

hmWanMbus6FValue2D		OBJECT-TYPE
			SYNTAX	INTEGER
			MAX-ACCESS	read-only
			STATUS	current
			::= { hmWanMbus6F 97 }

hmWanMbus6FVIF2E		OBJECT-TYPE
			SYNTAX	INTEGER
			MAX-ACCESS	read-only
			STATUS	current
			::= { hmWanMbus6F 98 }

hmWanMbus6FValue2E		OBJECT-TYPE
			SYNTAX	INTEGER
			MAX-ACCESS	read-only
			STATUS	current
			::= { hmWanMbus6F 99 }

hmWanMbus6FVIF2F		OBJECT-TYPE
			SYNTAX	INTEGER
			MAX-ACCESS	read-only
			STATUS	current
			::= { hmWanMbus6F 100 }

hmWanMbus6FValue2F		OBJECT-TYPE
			SYNTAX	INTEGER
			MAX-ACCESS	read-only
			STATUS	current
			::= { hmWanMbus6F 101 }

hmWanMbus70			OBJECT IDENTIFIER ::= { hmWanMbus 112 }

hmWanMbus70IdNumber		OBJECT-TYPE
			SYNTAX	Gauge32
			MAX-ACCESS	read-only
			STATUS	current
			::= { hmWanMbus70 1 }

hmWanMbus70Manufacturer	OBJECT-TYPE
			SYNTAX	Gauge32
			MAX-ACCESS	read-only
			STATUS	current
			::= { hmWanMbus70 2 }

hmWanMbus70Version		OBJECT-TYPE
			SYNTAX	Gauge32
			MAX-ACCESS	read-only
			STATUS	current
			::= { hmWanMbus70 3 }

hmWanMbus70Medium		OBJECT-TYPE
			SYNTAX	Gauge32
			MAX-ACCESS	read-only
			STATUS	current
			::= { hmWanMbus70 4 }

hmWanMbus70Status		OBJECT-TYPE
			SYNTAX	Gauge32
			MAX-ACCESS	read-only
			STATUS	current
			::= { hmWanMbus70 5 }

hmWanMbus70VIF00		OBJECT-TYPE
			SYNTAX	INTEGER
			MAX-ACCESS	read-only
			STATUS	current
			::= { hmWanMbus70 6 }

hmWanMbus70Value00		OBJECT-TYPE
			SYNTAX	INTEGER
			MAX-ACCESS	read-only
			STATUS	current
			::= { hmWanMbus70 7 }

hmWanMbus70VIF01		OBJECT-TYPE
			SYNTAX	INTEGER
			MAX-ACCESS	read-only
			STATUS	current
			::= { hmWanMbus70 8 }

hmWanMbus70Value01		OBJECT-TYPE
			SYNTAX	INTEGER
			MAX-ACCESS	read-only
			STATUS	current
			::= { hmWanMbus70 9 }

hmWanMbus70VIF02		OBJECT-TYPE
			SYNTAX	INTEGER
			MAX-ACCESS	read-only
			STATUS	current
			::= { hmWanMbus70 10 }

hmWanMbus70Value02		OBJECT-TYPE
			SYNTAX	INTEGER
			MAX-ACCESS	read-only
			STATUS	current
			::= { hmWanMbus70 11 }

hmWanMbus70VIF03		OBJECT-TYPE
			SYNTAX	INTEGER
			MAX-ACCESS	read-only
			STATUS	current
			::= { hmWanMbus70 12 }

hmWanMbus70Value03		OBJECT-TYPE
			SYNTAX	INTEGER
			MAX-ACCESS	read-only
			STATUS	current
			::= { hmWanMbus70 13 }

hmWanMbus70VIF04		OBJECT-TYPE
			SYNTAX	INTEGER
			MAX-ACCESS	read-only
			STATUS	current
			::= { hmWanMbus70 14 }

hmWanMbus70Value04		OBJECT-TYPE
			SYNTAX	INTEGER
			MAX-ACCESS	read-only
			STATUS	current
			::= { hmWanMbus70 15 }

hmWanMbus70VIF05		OBJECT-TYPE
			SYNTAX	INTEGER
			MAX-ACCESS	read-only
			STATUS	current
			::= { hmWanMbus70 16 }

hmWanMbus70Value05		OBJECT-TYPE
			SYNTAX	INTEGER
			MAX-ACCESS	read-only
			STATUS	current
			::= { hmWanMbus70 17 }

hmWanMbus70VIF06		OBJECT-TYPE
			SYNTAX	INTEGER
			MAX-ACCESS	read-only
			STATUS	current
			::= { hmWanMbus70 18 }

hmWanMbus70Value06		OBJECT-TYPE
			SYNTAX	INTEGER
			MAX-ACCESS	read-only
			STATUS	current
			::= { hmWanMbus70 19 }

hmWanMbus70VIF07		OBJECT-TYPE
			SYNTAX	INTEGER
			MAX-ACCESS	read-only
			STATUS	current
			::= { hmWanMbus70 20 }

hmWanMbus70Value07		OBJECT-TYPE
			SYNTAX	INTEGER
			MAX-ACCESS	read-only
			STATUS	current
			::= { hmWanMbus70 21 }

hmWanMbus70VIF08		OBJECT-TYPE
			SYNTAX	INTEGER
			MAX-ACCESS	read-only
			STATUS	current
			::= { hmWanMbus70 22 }

hmWanMbus70Value08		OBJECT-TYPE
			SYNTAX	INTEGER
			MAX-ACCESS	read-only
			STATUS	current
			::= { hmWanMbus70 23 }

hmWanMbus70VIF09		OBJECT-TYPE
			SYNTAX	INTEGER
			MAX-ACCESS	read-only
			STATUS	current
			::= { hmWanMbus70 24 }

hmWanMbus70Value09		OBJECT-TYPE
			SYNTAX	INTEGER
			MAX-ACCESS	read-only
			STATUS	current
			::= { hmWanMbus70 25 }

hmWanMbus70VIF0A		OBJECT-TYPE
			SYNTAX	INTEGER
			MAX-ACCESS	read-only
			STATUS	current
			::= { hmWanMbus70 26 }

hmWanMbus70Value0A		OBJECT-TYPE
			SYNTAX	INTEGER
			MAX-ACCESS	read-only
			STATUS	current
			::= { hmWanMbus70 27 }

hmWanMbus70VIF0B		OBJECT-TYPE
			SYNTAX	INTEGER
			MAX-ACCESS	read-only
			STATUS	current
			::= { hmWanMbus70 28 }

hmWanMbus70Value0B		OBJECT-TYPE
			SYNTAX	INTEGER
			MAX-ACCESS	read-only
			STATUS	current
			::= { hmWanMbus70 29 }

hmWanMbus70VIF0C		OBJECT-TYPE
			SYNTAX	INTEGER
			MAX-ACCESS	read-only
			STATUS	current
			::= { hmWanMbus70 30 }

hmWanMbus70Value0C		OBJECT-TYPE
			SYNTAX	INTEGER
			MAX-ACCESS	read-only
			STATUS	current
			::= { hmWanMbus70 31 }

hmWanMbus70VIF0D		OBJECT-TYPE
			SYNTAX	INTEGER
			MAX-ACCESS	read-only
			STATUS	current
			::= { hmWanMbus70 32 }

hmWanMbus70Value0D		OBJECT-TYPE
			SYNTAX	INTEGER
			MAX-ACCESS	read-only
			STATUS	current
			::= { hmWanMbus70 33 }

hmWanMbus70VIF0E		OBJECT-TYPE
			SYNTAX	INTEGER
			MAX-ACCESS	read-only
			STATUS	current
			::= { hmWanMbus70 34 }

hmWanMbus70Value0E		OBJECT-TYPE
			SYNTAX	INTEGER
			MAX-ACCESS	read-only
			STATUS	current
			::= { hmWanMbus70 35 }

hmWanMbus70VIF0F		OBJECT-TYPE
			SYNTAX	INTEGER
			MAX-ACCESS	read-only
			STATUS	current
			::= { hmWanMbus70 36 }

hmWanMbus70Value0F		OBJECT-TYPE
			SYNTAX	INTEGER
			MAX-ACCESS	read-only
			STATUS	current
			::= { hmWanMbus70 37 }

hmWanMbus70VIF10		OBJECT-TYPE
			SYNTAX	INTEGER
			MAX-ACCESS	read-only
			STATUS	current
			::= { hmWanMbus70 38 }

hmWanMbus70Value10		OBJECT-TYPE
			SYNTAX	INTEGER
			MAX-ACCESS	read-only
			STATUS	current
			::= { hmWanMbus70 39 }

hmWanMbus70VIF11		OBJECT-TYPE
			SYNTAX	INTEGER
			MAX-ACCESS	read-only
			STATUS	current
			::= { hmWanMbus70 40 }

hmWanMbus70Value11		OBJECT-TYPE
			SYNTAX	INTEGER
			MAX-ACCESS	read-only
			STATUS	current
			::= { hmWanMbus70 41 }

hmWanMbus70VIF12		OBJECT-TYPE
			SYNTAX	INTEGER
			MAX-ACCESS	read-only
			STATUS	current
			::= { hmWanMbus70 42 }

hmWanMbus70Value12		OBJECT-TYPE
			SYNTAX	INTEGER
			MAX-ACCESS	read-only
			STATUS	current
			::= { hmWanMbus70 43 }

hmWanMbus70VIF13		OBJECT-TYPE
			SYNTAX	INTEGER
			MAX-ACCESS	read-only
			STATUS	current
			::= { hmWanMbus70 44 }

hmWanMbus70Value13		OBJECT-TYPE
			SYNTAX	INTEGER
			MAX-ACCESS	read-only
			STATUS	current
			::= { hmWanMbus70 45 }

hmWanMbus70VIF14		OBJECT-TYPE
			SYNTAX	INTEGER
			MAX-ACCESS	read-only
			STATUS	current
			::= { hmWanMbus70 46 }

hmWanMbus70Value14		OBJECT-TYPE
			SYNTAX	INTEGER
			MAX-ACCESS	read-only
			STATUS	current
			::= { hmWanMbus70 47 }

hmWanMbus70VIF15		OBJECT-TYPE
			SYNTAX	INTEGER
			MAX-ACCESS	read-only
			STATUS	current
			::= { hmWanMbus70 48 }

hmWanMbus70Value15		OBJECT-TYPE
			SYNTAX	INTEGER
			MAX-ACCESS	read-only
			STATUS	current
			::= { hmWanMbus70 49 }

hmWanMbus70VIF16		OBJECT-TYPE
			SYNTAX	INTEGER
			MAX-ACCESS	read-only
			STATUS	current
			::= { hmWanMbus70 50 }

hmWanMbus70Value16		OBJECT-TYPE
			SYNTAX	INTEGER
			MAX-ACCESS	read-only
			STATUS	current
			::= { hmWanMbus70 51 }

hmWanMbus70VIF17		OBJECT-TYPE
			SYNTAX	INTEGER
			MAX-ACCESS	read-only
			STATUS	current
			::= { hmWanMbus70 52 }

hmWanMbus70Value17		OBJECT-TYPE
			SYNTAX	INTEGER
			MAX-ACCESS	read-only
			STATUS	current
			::= { hmWanMbus70 53 }

hmWanMbus70VIF18		OBJECT-TYPE
			SYNTAX	INTEGER
			MAX-ACCESS	read-only
			STATUS	current
			::= { hmWanMbus70 54 }

hmWanMbus70Value18		OBJECT-TYPE
			SYNTAX	INTEGER
			MAX-ACCESS	read-only
			STATUS	current
			::= { hmWanMbus70 55 }

hmWanMbus70VIF19		OBJECT-TYPE
			SYNTAX	INTEGER
			MAX-ACCESS	read-only
			STATUS	current
			::= { hmWanMbus70 56 }

hmWanMbus70Value19		OBJECT-TYPE
			SYNTAX	INTEGER
			MAX-ACCESS	read-only
			STATUS	current
			::= { hmWanMbus70 57 }

hmWanMbus70VIF1A		OBJECT-TYPE
			SYNTAX	INTEGER
			MAX-ACCESS	read-only
			STATUS	current
			::= { hmWanMbus70 58 }

hmWanMbus70Value1A		OBJECT-TYPE
			SYNTAX	INTEGER
			MAX-ACCESS	read-only
			STATUS	current
			::= { hmWanMbus70 59 }

hmWanMbus70VIF1B		OBJECT-TYPE
			SYNTAX	INTEGER
			MAX-ACCESS	read-only
			STATUS	current
			::= { hmWanMbus70 60 }

hmWanMbus70Value1B		OBJECT-TYPE
			SYNTAX	INTEGER
			MAX-ACCESS	read-only
			STATUS	current
			::= { hmWanMbus70 61 }

hmWanMbus70VIF1C		OBJECT-TYPE
			SYNTAX	INTEGER
			MAX-ACCESS	read-only
			STATUS	current
			::= { hmWanMbus70 62 }

hmWanMbus70Value1C		OBJECT-TYPE
			SYNTAX	INTEGER
			MAX-ACCESS	read-only
			STATUS	current
			::= { hmWanMbus70 63 }

hmWanMbus70VIF1D		OBJECT-TYPE
			SYNTAX	INTEGER
			MAX-ACCESS	read-only
			STATUS	current
			::= { hmWanMbus70 64 }

hmWanMbus70Value1D		OBJECT-TYPE
			SYNTAX	INTEGER
			MAX-ACCESS	read-only
			STATUS	current
			::= { hmWanMbus70 65 }

hmWanMbus70VIF1E		OBJECT-TYPE
			SYNTAX	INTEGER
			MAX-ACCESS	read-only
			STATUS	current
			::= { hmWanMbus70 66 }

hmWanMbus70Value1E		OBJECT-TYPE
			SYNTAX	INTEGER
			MAX-ACCESS	read-only
			STATUS	current
			::= { hmWanMbus70 67 }

hmWanMbus70VIF1F		OBJECT-TYPE
			SYNTAX	INTEGER
			MAX-ACCESS	read-only
			STATUS	current
			::= { hmWanMbus70 68 }

hmWanMbus70Value1F		OBJECT-TYPE
			SYNTAX	INTEGER
			MAX-ACCESS	read-only
			STATUS	current
			::= { hmWanMbus70 69 }

hmWanMbus70VIF20		OBJECT-TYPE
			SYNTAX	INTEGER
			MAX-ACCESS	read-only
			STATUS	current
			::= { hmWanMbus70 70 }

hmWanMbus70Value20		OBJECT-TYPE
			SYNTAX	INTEGER
			MAX-ACCESS	read-only
			STATUS	current
			::= { hmWanMbus70 71 }

hmWanMbus70VIF21		OBJECT-TYPE
			SYNTAX	INTEGER
			MAX-ACCESS	read-only
			STATUS	current
			::= { hmWanMbus70 72 }

hmWanMbus70Value21		OBJECT-TYPE
			SYNTAX	INTEGER
			MAX-ACCESS	read-only
			STATUS	current
			::= { hmWanMbus70 73 }

hmWanMbus70VIF22		OBJECT-TYPE
			SYNTAX	INTEGER
			MAX-ACCESS	read-only
			STATUS	current
			::= { hmWanMbus70 74 }

hmWanMbus70Value22		OBJECT-TYPE
			SYNTAX	INTEGER
			MAX-ACCESS	read-only
			STATUS	current
			::= { hmWanMbus70 75 }

hmWanMbus70VIF23		OBJECT-TYPE
			SYNTAX	INTEGER
			MAX-ACCESS	read-only
			STATUS	current
			::= { hmWanMbus70 76 }

hmWanMbus70Value23		OBJECT-TYPE
			SYNTAX	INTEGER
			MAX-ACCESS	read-only
			STATUS	current
			::= { hmWanMbus70 77 }

hmWanMbus70VIF24		OBJECT-TYPE
			SYNTAX	INTEGER
			MAX-ACCESS	read-only
			STATUS	current
			::= { hmWanMbus70 78 }

hmWanMbus70Value24		OBJECT-TYPE
			SYNTAX	INTEGER
			MAX-ACCESS	read-only
			STATUS	current
			::= { hmWanMbus70 79 }

hmWanMbus70VIF25		OBJECT-TYPE
			SYNTAX	INTEGER
			MAX-ACCESS	read-only
			STATUS	current
			::= { hmWanMbus70 80 }

hmWanMbus70Value25		OBJECT-TYPE
			SYNTAX	INTEGER
			MAX-ACCESS	read-only
			STATUS	current
			::= { hmWanMbus70 81 }

hmWanMbus70VIF26		OBJECT-TYPE
			SYNTAX	INTEGER
			MAX-ACCESS	read-only
			STATUS	current
			::= { hmWanMbus70 82 }

hmWanMbus70Value26		OBJECT-TYPE
			SYNTAX	INTEGER
			MAX-ACCESS	read-only
			STATUS	current
			::= { hmWanMbus70 83 }

hmWanMbus70VIF27		OBJECT-TYPE
			SYNTAX	INTEGER
			MAX-ACCESS	read-only
			STATUS	current
			::= { hmWanMbus70 84 }

hmWanMbus70Value27		OBJECT-TYPE
			SYNTAX	INTEGER
			MAX-ACCESS	read-only
			STATUS	current
			::= { hmWanMbus70 85 }

hmWanMbus70VIF28		OBJECT-TYPE
			SYNTAX	INTEGER
			MAX-ACCESS	read-only
			STATUS	current
			::= { hmWanMbus70 86 }

hmWanMbus70Value28		OBJECT-TYPE
			SYNTAX	INTEGER
			MAX-ACCESS	read-only
			STATUS	current
			::= { hmWanMbus70 87 }

hmWanMbus70VIF29		OBJECT-TYPE
			SYNTAX	INTEGER
			MAX-ACCESS	read-only
			STATUS	current
			::= { hmWanMbus70 88 }

hmWanMbus70Value29		OBJECT-TYPE
			SYNTAX	INTEGER
			MAX-ACCESS	read-only
			STATUS	current
			::= { hmWanMbus70 89 }

hmWanMbus70VIF2A		OBJECT-TYPE
			SYNTAX	INTEGER
			MAX-ACCESS	read-only
			STATUS	current
			::= { hmWanMbus70 90 }

hmWanMbus70Value2A		OBJECT-TYPE
			SYNTAX	INTEGER
			MAX-ACCESS	read-only
			STATUS	current
			::= { hmWanMbus70 91 }

hmWanMbus70VIF2B		OBJECT-TYPE
			SYNTAX	INTEGER
			MAX-ACCESS	read-only
			STATUS	current
			::= { hmWanMbus70 92 }

hmWanMbus70Value2B		OBJECT-TYPE
			SYNTAX	INTEGER
			MAX-ACCESS	read-only
			STATUS	current
			::= { hmWanMbus70 93 }

hmWanMbus70VIF2C		OBJECT-TYPE
			SYNTAX	INTEGER
			MAX-ACCESS	read-only
			STATUS	current
			::= { hmWanMbus70 94 }

hmWanMbus70Value2C		OBJECT-TYPE
			SYNTAX	INTEGER
			MAX-ACCESS	read-only
			STATUS	current
			::= { hmWanMbus70 95 }

hmWanMbus70VIF2D		OBJECT-TYPE
			SYNTAX	INTEGER
			MAX-ACCESS	read-only
			STATUS	current
			::= { hmWanMbus70 96 }

hmWanMbus70Value2D		OBJECT-TYPE
			SYNTAX	INTEGER
			MAX-ACCESS	read-only
			STATUS	current
			::= { hmWanMbus70 97 }

hmWanMbus70VIF2E		OBJECT-TYPE
			SYNTAX	INTEGER
			MAX-ACCESS	read-only
			STATUS	current
			::= { hmWanMbus70 98 }

hmWanMbus70Value2E		OBJECT-TYPE
			SYNTAX	INTEGER
			MAX-ACCESS	read-only
			STATUS	current
			::= { hmWanMbus70 99 }

hmWanMbus70VIF2F		OBJECT-TYPE
			SYNTAX	INTEGER
			MAX-ACCESS	read-only
			STATUS	current
			::= { hmWanMbus70 100 }

hmWanMbus70Value2F		OBJECT-TYPE
			SYNTAX	INTEGER
			MAX-ACCESS	read-only
			STATUS	current
			::= { hmWanMbus70 101 }

hmWanMbus71			OBJECT IDENTIFIER ::= { hmWanMbus 113 }

hmWanMbus71IdNumber		OBJECT-TYPE
			SYNTAX	Gauge32
			MAX-ACCESS	read-only
			STATUS	current
			::= { hmWanMbus71 1 }

hmWanMbus71Manufacturer	OBJECT-TYPE
			SYNTAX	Gauge32
			MAX-ACCESS	read-only
			STATUS	current
			::= { hmWanMbus71 2 }

hmWanMbus71Version		OBJECT-TYPE
			SYNTAX	Gauge32
			MAX-ACCESS	read-only
			STATUS	current
			::= { hmWanMbus71 3 }

hmWanMbus71Medium		OBJECT-TYPE
			SYNTAX	Gauge32
			MAX-ACCESS	read-only
			STATUS	current
			::= { hmWanMbus71 4 }

hmWanMbus71Status		OBJECT-TYPE
			SYNTAX	Gauge32
			MAX-ACCESS	read-only
			STATUS	current
			::= { hmWanMbus71 5 }

hmWanMbus71VIF00		OBJECT-TYPE
			SYNTAX	INTEGER
			MAX-ACCESS	read-only
			STATUS	current
			::= { hmWanMbus71 6 }

hmWanMbus71Value00		OBJECT-TYPE
			SYNTAX	INTEGER
			MAX-ACCESS	read-only
			STATUS	current
			::= { hmWanMbus71 7 }

hmWanMbus71VIF01		OBJECT-TYPE
			SYNTAX	INTEGER
			MAX-ACCESS	read-only
			STATUS	current
			::= { hmWanMbus71 8 }

hmWanMbus71Value01		OBJECT-TYPE
			SYNTAX	INTEGER
			MAX-ACCESS	read-only
			STATUS	current
			::= { hmWanMbus71 9 }

hmWanMbus71VIF02		OBJECT-TYPE
			SYNTAX	INTEGER
			MAX-ACCESS	read-only
			STATUS	current
			::= { hmWanMbus71 10 }

hmWanMbus71Value02		OBJECT-TYPE
			SYNTAX	INTEGER
			MAX-ACCESS	read-only
			STATUS	current
			::= { hmWanMbus71 11 }

hmWanMbus71VIF03		OBJECT-TYPE
			SYNTAX	INTEGER
			MAX-ACCESS	read-only
			STATUS	current
			::= { hmWanMbus71 12 }

hmWanMbus71Value03		OBJECT-TYPE
			SYNTAX	INTEGER
			MAX-ACCESS	read-only
			STATUS	current
			::= { hmWanMbus71 13 }

hmWanMbus71VIF04		OBJECT-TYPE
			SYNTAX	INTEGER
			MAX-ACCESS	read-only
			STATUS	current
			::= { hmWanMbus71 14 }

hmWanMbus71Value04		OBJECT-TYPE
			SYNTAX	INTEGER
			MAX-ACCESS	read-only
			STATUS	current
			::= { hmWanMbus71 15 }

hmWanMbus71VIF05		OBJECT-TYPE
			SYNTAX	INTEGER
			MAX-ACCESS	read-only
			STATUS	current
			::= { hmWanMbus71 16 }

hmWanMbus71Value05		OBJECT-TYPE
			SYNTAX	INTEGER
			MAX-ACCESS	read-only
			STATUS	current
			::= { hmWanMbus71 17 }

hmWanMbus71VIF06		OBJECT-TYPE
			SYNTAX	INTEGER
			MAX-ACCESS	read-only
			STATUS	current
			::= { hmWanMbus71 18 }

hmWanMbus71Value06		OBJECT-TYPE
			SYNTAX	INTEGER
			MAX-ACCESS	read-only
			STATUS	current
			::= { hmWanMbus71 19 }

hmWanMbus71VIF07		OBJECT-TYPE
			SYNTAX	INTEGER
			MAX-ACCESS	read-only
			STATUS	current
			::= { hmWanMbus71 20 }

hmWanMbus71Value07		OBJECT-TYPE
			SYNTAX	INTEGER
			MAX-ACCESS	read-only
			STATUS	current
			::= { hmWanMbus71 21 }

hmWanMbus71VIF08		OBJECT-TYPE
			SYNTAX	INTEGER
			MAX-ACCESS	read-only
			STATUS	current
			::= { hmWanMbus71 22 }

hmWanMbus71Value08		OBJECT-TYPE
			SYNTAX	INTEGER
			MAX-ACCESS	read-only
			STATUS	current
			::= { hmWanMbus71 23 }

hmWanMbus71VIF09		OBJECT-TYPE
			SYNTAX	INTEGER
			MAX-ACCESS	read-only
			STATUS	current
			::= { hmWanMbus71 24 }

hmWanMbus71Value09		OBJECT-TYPE
			SYNTAX	INTEGER
			MAX-ACCESS	read-only
			STATUS	current
			::= { hmWanMbus71 25 }

hmWanMbus71VIF0A		OBJECT-TYPE
			SYNTAX	INTEGER
			MAX-ACCESS	read-only
			STATUS	current
			::= { hmWanMbus71 26 }

hmWanMbus71Value0A		OBJECT-TYPE
			SYNTAX	INTEGER
			MAX-ACCESS	read-only
			STATUS	current
			::= { hmWanMbus71 27 }

hmWanMbus71VIF0B		OBJECT-TYPE
			SYNTAX	INTEGER
			MAX-ACCESS	read-only
			STATUS	current
			::= { hmWanMbus71 28 }

hmWanMbus71Value0B		OBJECT-TYPE
			SYNTAX	INTEGER
			MAX-ACCESS	read-only
			STATUS	current
			::= { hmWanMbus71 29 }

hmWanMbus71VIF0C		OBJECT-TYPE
			SYNTAX	INTEGER
			MAX-ACCESS	read-only
			STATUS	current
			::= { hmWanMbus71 30 }

hmWanMbus71Value0C		OBJECT-TYPE
			SYNTAX	INTEGER
			MAX-ACCESS	read-only
			STATUS	current
			::= { hmWanMbus71 31 }

hmWanMbus71VIF0D		OBJECT-TYPE
			SYNTAX	INTEGER
			MAX-ACCESS	read-only
			STATUS	current
			::= { hmWanMbus71 32 }

hmWanMbus71Value0D		OBJECT-TYPE
			SYNTAX	INTEGER
			MAX-ACCESS	read-only
			STATUS	current
			::= { hmWanMbus71 33 }

hmWanMbus71VIF0E		OBJECT-TYPE
			SYNTAX	INTEGER
			MAX-ACCESS	read-only
			STATUS	current
			::= { hmWanMbus71 34 }

hmWanMbus71Value0E		OBJECT-TYPE
			SYNTAX	INTEGER
			MAX-ACCESS	read-only
			STATUS	current
			::= { hmWanMbus71 35 }

hmWanMbus71VIF0F		OBJECT-TYPE
			SYNTAX	INTEGER
			MAX-ACCESS	read-only
			STATUS	current
			::= { hmWanMbus71 36 }

hmWanMbus71Value0F		OBJECT-TYPE
			SYNTAX	INTEGER
			MAX-ACCESS	read-only
			STATUS	current
			::= { hmWanMbus71 37 }

hmWanMbus71VIF10		OBJECT-TYPE
			SYNTAX	INTEGER
			MAX-ACCESS	read-only
			STATUS	current
			::= { hmWanMbus71 38 }

hmWanMbus71Value10		OBJECT-TYPE
			SYNTAX	INTEGER
			MAX-ACCESS	read-only
			STATUS	current
			::= { hmWanMbus71 39 }

hmWanMbus71VIF11		OBJECT-TYPE
			SYNTAX	INTEGER
			MAX-ACCESS	read-only
			STATUS	current
			::= { hmWanMbus71 40 }

hmWanMbus71Value11		OBJECT-TYPE
			SYNTAX	INTEGER
			MAX-ACCESS	read-only
			STATUS	current
			::= { hmWanMbus71 41 }

hmWanMbus71VIF12		OBJECT-TYPE
			SYNTAX	INTEGER
			MAX-ACCESS	read-only
			STATUS	current
			::= { hmWanMbus71 42 }

hmWanMbus71Value12		OBJECT-TYPE
			SYNTAX	INTEGER
			MAX-ACCESS	read-only
			STATUS	current
			::= { hmWanMbus71 43 }

hmWanMbus71VIF13		OBJECT-TYPE
			SYNTAX	INTEGER
			MAX-ACCESS	read-only
			STATUS	current
			::= { hmWanMbus71 44 }

hmWanMbus71Value13		OBJECT-TYPE
			SYNTAX	INTEGER
			MAX-ACCESS	read-only
			STATUS	current
			::= { hmWanMbus71 45 }

hmWanMbus71VIF14		OBJECT-TYPE
			SYNTAX	INTEGER
			MAX-ACCESS	read-only
			STATUS	current
			::= { hmWanMbus71 46 }

hmWanMbus71Value14		OBJECT-TYPE
			SYNTAX	INTEGER
			MAX-ACCESS	read-only
			STATUS	current
			::= { hmWanMbus71 47 }

hmWanMbus71VIF15		OBJECT-TYPE
			SYNTAX	INTEGER
			MAX-ACCESS	read-only
			STATUS	current
			::= { hmWanMbus71 48 }

hmWanMbus71Value15		OBJECT-TYPE
			SYNTAX	INTEGER
			MAX-ACCESS	read-only
			STATUS	current
			::= { hmWanMbus71 49 }

hmWanMbus71VIF16		OBJECT-TYPE
			SYNTAX	INTEGER
			MAX-ACCESS	read-only
			STATUS	current
			::= { hmWanMbus71 50 }

hmWanMbus71Value16		OBJECT-TYPE
			SYNTAX	INTEGER
			MAX-ACCESS	read-only
			STATUS	current
			::= { hmWanMbus71 51 }

hmWanMbus71VIF17		OBJECT-TYPE
			SYNTAX	INTEGER
			MAX-ACCESS	read-only
			STATUS	current
			::= { hmWanMbus71 52 }

hmWanMbus71Value17		OBJECT-TYPE
			SYNTAX	INTEGER
			MAX-ACCESS	read-only
			STATUS	current
			::= { hmWanMbus71 53 }

hmWanMbus71VIF18		OBJECT-TYPE
			SYNTAX	INTEGER
			MAX-ACCESS	read-only
			STATUS	current
			::= { hmWanMbus71 54 }

hmWanMbus71Value18		OBJECT-TYPE
			SYNTAX	INTEGER
			MAX-ACCESS	read-only
			STATUS	current
			::= { hmWanMbus71 55 }

hmWanMbus71VIF19		OBJECT-TYPE
			SYNTAX	INTEGER
			MAX-ACCESS	read-only
			STATUS	current
			::= { hmWanMbus71 56 }

hmWanMbus71Value19		OBJECT-TYPE
			SYNTAX	INTEGER
			MAX-ACCESS	read-only
			STATUS	current
			::= { hmWanMbus71 57 }

hmWanMbus71VIF1A		OBJECT-TYPE
			SYNTAX	INTEGER
			MAX-ACCESS	read-only
			STATUS	current
			::= { hmWanMbus71 58 }

hmWanMbus71Value1A		OBJECT-TYPE
			SYNTAX	INTEGER
			MAX-ACCESS	read-only
			STATUS	current
			::= { hmWanMbus71 59 }

hmWanMbus71VIF1B		OBJECT-TYPE
			SYNTAX	INTEGER
			MAX-ACCESS	read-only
			STATUS	current
			::= { hmWanMbus71 60 }

hmWanMbus71Value1B		OBJECT-TYPE
			SYNTAX	INTEGER
			MAX-ACCESS	read-only
			STATUS	current
			::= { hmWanMbus71 61 }

hmWanMbus71VIF1C		OBJECT-TYPE
			SYNTAX	INTEGER
			MAX-ACCESS	read-only
			STATUS	current
			::= { hmWanMbus71 62 }

hmWanMbus71Value1C		OBJECT-TYPE
			SYNTAX	INTEGER
			MAX-ACCESS	read-only
			STATUS	current
			::= { hmWanMbus71 63 }

hmWanMbus71VIF1D		OBJECT-TYPE
			SYNTAX	INTEGER
			MAX-ACCESS	read-only
			STATUS	current
			::= { hmWanMbus71 64 }

hmWanMbus71Value1D		OBJECT-TYPE
			SYNTAX	INTEGER
			MAX-ACCESS	read-only
			STATUS	current
			::= { hmWanMbus71 65 }

hmWanMbus71VIF1E		OBJECT-TYPE
			SYNTAX	INTEGER
			MAX-ACCESS	read-only
			STATUS	current
			::= { hmWanMbus71 66 }

hmWanMbus71Value1E		OBJECT-TYPE
			SYNTAX	INTEGER
			MAX-ACCESS	read-only
			STATUS	current
			::= { hmWanMbus71 67 }

hmWanMbus71VIF1F		OBJECT-TYPE
			SYNTAX	INTEGER
			MAX-ACCESS	read-only
			STATUS	current
			::= { hmWanMbus71 68 }

hmWanMbus71Value1F		OBJECT-TYPE
			SYNTAX	INTEGER
			MAX-ACCESS	read-only
			STATUS	current
			::= { hmWanMbus71 69 }

hmWanMbus71VIF20		OBJECT-TYPE
			SYNTAX	INTEGER
			MAX-ACCESS	read-only
			STATUS	current
			::= { hmWanMbus71 70 }

hmWanMbus71Value20		OBJECT-TYPE
			SYNTAX	INTEGER
			MAX-ACCESS	read-only
			STATUS	current
			::= { hmWanMbus71 71 }

hmWanMbus71VIF21		OBJECT-TYPE
			SYNTAX	INTEGER
			MAX-ACCESS	read-only
			STATUS	current
			::= { hmWanMbus71 72 }

hmWanMbus71Value21		OBJECT-TYPE
			SYNTAX	INTEGER
			MAX-ACCESS	read-only
			STATUS	current
			::= { hmWanMbus71 73 }

hmWanMbus71VIF22		OBJECT-TYPE
			SYNTAX	INTEGER
			MAX-ACCESS	read-only
			STATUS	current
			::= { hmWanMbus71 74 }

hmWanMbus71Value22		OBJECT-TYPE
			SYNTAX	INTEGER
			MAX-ACCESS	read-only
			STATUS	current
			::= { hmWanMbus71 75 }

hmWanMbus71VIF23		OBJECT-TYPE
			SYNTAX	INTEGER
			MAX-ACCESS	read-only
			STATUS	current
			::= { hmWanMbus71 76 }

hmWanMbus71Value23		OBJECT-TYPE
			SYNTAX	INTEGER
			MAX-ACCESS	read-only
			STATUS	current
			::= { hmWanMbus71 77 }

hmWanMbus71VIF24		OBJECT-TYPE
			SYNTAX	INTEGER
			MAX-ACCESS	read-only
			STATUS	current
			::= { hmWanMbus71 78 }

hmWanMbus71Value24		OBJECT-TYPE
			SYNTAX	INTEGER
			MAX-ACCESS	read-only
			STATUS	current
			::= { hmWanMbus71 79 }

hmWanMbus71VIF25		OBJECT-TYPE
			SYNTAX	INTEGER
			MAX-ACCESS	read-only
			STATUS	current
			::= { hmWanMbus71 80 }

hmWanMbus71Value25		OBJECT-TYPE
			SYNTAX	INTEGER
			MAX-ACCESS	read-only
			STATUS	current
			::= { hmWanMbus71 81 }

hmWanMbus71VIF26		OBJECT-TYPE
			SYNTAX	INTEGER
			MAX-ACCESS	read-only
			STATUS	current
			::= { hmWanMbus71 82 }

hmWanMbus71Value26		OBJECT-TYPE
			SYNTAX	INTEGER
			MAX-ACCESS	read-only
			STATUS	current
			::= { hmWanMbus71 83 }

hmWanMbus71VIF27		OBJECT-TYPE
			SYNTAX	INTEGER
			MAX-ACCESS	read-only
			STATUS	current
			::= { hmWanMbus71 84 }

hmWanMbus71Value27		OBJECT-TYPE
			SYNTAX	INTEGER
			MAX-ACCESS	read-only
			STATUS	current
			::= { hmWanMbus71 85 }

hmWanMbus71VIF28		OBJECT-TYPE
			SYNTAX	INTEGER
			MAX-ACCESS	read-only
			STATUS	current
			::= { hmWanMbus71 86 }

hmWanMbus71Value28		OBJECT-TYPE
			SYNTAX	INTEGER
			MAX-ACCESS	read-only
			STATUS	current
			::= { hmWanMbus71 87 }

hmWanMbus71VIF29		OBJECT-TYPE
			SYNTAX	INTEGER
			MAX-ACCESS	read-only
			STATUS	current
			::= { hmWanMbus71 88 }

hmWanMbus71Value29		OBJECT-TYPE
			SYNTAX	INTEGER
			MAX-ACCESS	read-only
			STATUS	current
			::= { hmWanMbus71 89 }

hmWanMbus71VIF2A		OBJECT-TYPE
			SYNTAX	INTEGER
			MAX-ACCESS	read-only
			STATUS	current
			::= { hmWanMbus71 90 }

hmWanMbus71Value2A		OBJECT-TYPE
			SYNTAX	INTEGER
			MAX-ACCESS	read-only
			STATUS	current
			::= { hmWanMbus71 91 }

hmWanMbus71VIF2B		OBJECT-TYPE
			SYNTAX	INTEGER
			MAX-ACCESS	read-only
			STATUS	current
			::= { hmWanMbus71 92 }

hmWanMbus71Value2B		OBJECT-TYPE
			SYNTAX	INTEGER
			MAX-ACCESS	read-only
			STATUS	current
			::= { hmWanMbus71 93 }

hmWanMbus71VIF2C		OBJECT-TYPE
			SYNTAX	INTEGER
			MAX-ACCESS	read-only
			STATUS	current
			::= { hmWanMbus71 94 }

hmWanMbus71Value2C		OBJECT-TYPE
			SYNTAX	INTEGER
			MAX-ACCESS	read-only
			STATUS	current
			::= { hmWanMbus71 95 }

hmWanMbus71VIF2D		OBJECT-TYPE
			SYNTAX	INTEGER
			MAX-ACCESS	read-only
			STATUS	current
			::= { hmWanMbus71 96 }

hmWanMbus71Value2D		OBJECT-TYPE
			SYNTAX	INTEGER
			MAX-ACCESS	read-only
			STATUS	current
			::= { hmWanMbus71 97 }

hmWanMbus71VIF2E		OBJECT-TYPE
			SYNTAX	INTEGER
			MAX-ACCESS	read-only
			STATUS	current
			::= { hmWanMbus71 98 }

hmWanMbus71Value2E		OBJECT-TYPE
			SYNTAX	INTEGER
			MAX-ACCESS	read-only
			STATUS	current
			::= { hmWanMbus71 99 }

hmWanMbus71VIF2F		OBJECT-TYPE
			SYNTAX	INTEGER
			MAX-ACCESS	read-only
			STATUS	current
			::= { hmWanMbus71 100 }

hmWanMbus71Value2F		OBJECT-TYPE
			SYNTAX	INTEGER
			MAX-ACCESS	read-only
			STATUS	current
			::= { hmWanMbus71 101 }

hmWanMbus72			OBJECT IDENTIFIER ::= { hmWanMbus 114 }

hmWanMbus72IdNumber		OBJECT-TYPE
			SYNTAX	Gauge32
			MAX-ACCESS	read-only
			STATUS	current
			::= { hmWanMbus72 1 }

hmWanMbus72Manufacturer	OBJECT-TYPE
			SYNTAX	Gauge32
			MAX-ACCESS	read-only
			STATUS	current
			::= { hmWanMbus72 2 }

hmWanMbus72Version		OBJECT-TYPE
			SYNTAX	Gauge32
			MAX-ACCESS	read-only
			STATUS	current
			::= { hmWanMbus72 3 }

hmWanMbus72Medium		OBJECT-TYPE
			SYNTAX	Gauge32
			MAX-ACCESS	read-only
			STATUS	current
			::= { hmWanMbus72 4 }

hmWanMbus72Status		OBJECT-TYPE
			SYNTAX	Gauge32
			MAX-ACCESS	read-only
			STATUS	current
			::= { hmWanMbus72 5 }

hmWanMbus72VIF00		OBJECT-TYPE
			SYNTAX	INTEGER
			MAX-ACCESS	read-only
			STATUS	current
			::= { hmWanMbus72 6 }

hmWanMbus72Value00		OBJECT-TYPE
			SYNTAX	INTEGER
			MAX-ACCESS	read-only
			STATUS	current
			::= { hmWanMbus72 7 }

hmWanMbus72VIF01		OBJECT-TYPE
			SYNTAX	INTEGER
			MAX-ACCESS	read-only
			STATUS	current
			::= { hmWanMbus72 8 }

hmWanMbus72Value01		OBJECT-TYPE
			SYNTAX	INTEGER
			MAX-ACCESS	read-only
			STATUS	current
			::= { hmWanMbus72 9 }

hmWanMbus72VIF02		OBJECT-TYPE
			SYNTAX	INTEGER
			MAX-ACCESS	read-only
			STATUS	current
			::= { hmWanMbus72 10 }

hmWanMbus72Value02		OBJECT-TYPE
			SYNTAX	INTEGER
			MAX-ACCESS	read-only
			STATUS	current
			::= { hmWanMbus72 11 }

hmWanMbus72VIF03		OBJECT-TYPE
			SYNTAX	INTEGER
			MAX-ACCESS	read-only
			STATUS	current
			::= { hmWanMbus72 12 }

hmWanMbus72Value03		OBJECT-TYPE
			SYNTAX	INTEGER
			MAX-ACCESS	read-only
			STATUS	current
			::= { hmWanMbus72 13 }

hmWanMbus72VIF04		OBJECT-TYPE
			SYNTAX	INTEGER
			MAX-ACCESS	read-only
			STATUS	current
			::= { hmWanMbus72 14 }

hmWanMbus72Value04		OBJECT-TYPE
			SYNTAX	INTEGER
			MAX-ACCESS	read-only
			STATUS	current
			::= { hmWanMbus72 15 }

hmWanMbus72VIF05		OBJECT-TYPE
			SYNTAX	INTEGER
			MAX-ACCESS	read-only
			STATUS	current
			::= { hmWanMbus72 16 }

hmWanMbus72Value05		OBJECT-TYPE
			SYNTAX	INTEGER
			MAX-ACCESS	read-only
			STATUS	current
			::= { hmWanMbus72 17 }

hmWanMbus72VIF06		OBJECT-TYPE
			SYNTAX	INTEGER
			MAX-ACCESS	read-only
			STATUS	current
			::= { hmWanMbus72 18 }

hmWanMbus72Value06		OBJECT-TYPE
			SYNTAX	INTEGER
			MAX-ACCESS	read-only
			STATUS	current
			::= { hmWanMbus72 19 }

hmWanMbus72VIF07		OBJECT-TYPE
			SYNTAX	INTEGER
			MAX-ACCESS	read-only
			STATUS	current
			::= { hmWanMbus72 20 }

hmWanMbus72Value07		OBJECT-TYPE
			SYNTAX	INTEGER
			MAX-ACCESS	read-only
			STATUS	current
			::= { hmWanMbus72 21 }

hmWanMbus72VIF08		OBJECT-TYPE
			SYNTAX	INTEGER
			MAX-ACCESS	read-only
			STATUS	current
			::= { hmWanMbus72 22 }

hmWanMbus72Value08		OBJECT-TYPE
			SYNTAX	INTEGER
			MAX-ACCESS	read-only
			STATUS	current
			::= { hmWanMbus72 23 }

hmWanMbus72VIF09		OBJECT-TYPE
			SYNTAX	INTEGER
			MAX-ACCESS	read-only
			STATUS	current
			::= { hmWanMbus72 24 }

hmWanMbus72Value09		OBJECT-TYPE
			SYNTAX	INTEGER
			MAX-ACCESS	read-only
			STATUS	current
			::= { hmWanMbus72 25 }

hmWanMbus72VIF0A		OBJECT-TYPE
			SYNTAX	INTEGER
			MAX-ACCESS	read-only
			STATUS	current
			::= { hmWanMbus72 26 }

hmWanMbus72Value0A		OBJECT-TYPE
			SYNTAX	INTEGER
			MAX-ACCESS	read-only
			STATUS	current
			::= { hmWanMbus72 27 }

hmWanMbus72VIF0B		OBJECT-TYPE
			SYNTAX	INTEGER
			MAX-ACCESS	read-only
			STATUS	current
			::= { hmWanMbus72 28 }

hmWanMbus72Value0B		OBJECT-TYPE
			SYNTAX	INTEGER
			MAX-ACCESS	read-only
			STATUS	current
			::= { hmWanMbus72 29 }

hmWanMbus72VIF0C		OBJECT-TYPE
			SYNTAX	INTEGER
			MAX-ACCESS	read-only
			STATUS	current
			::= { hmWanMbus72 30 }

hmWanMbus72Value0C		OBJECT-TYPE
			SYNTAX	INTEGER
			MAX-ACCESS	read-only
			STATUS	current
			::= { hmWanMbus72 31 }

hmWanMbus72VIF0D		OBJECT-TYPE
			SYNTAX	INTEGER
			MAX-ACCESS	read-only
			STATUS	current
			::= { hmWanMbus72 32 }

hmWanMbus72Value0D		OBJECT-TYPE
			SYNTAX	INTEGER
			MAX-ACCESS	read-only
			STATUS	current
			::= { hmWanMbus72 33 }

hmWanMbus72VIF0E		OBJECT-TYPE
			SYNTAX	INTEGER
			MAX-ACCESS	read-only
			STATUS	current
			::= { hmWanMbus72 34 }

hmWanMbus72Value0E		OBJECT-TYPE
			SYNTAX	INTEGER
			MAX-ACCESS	read-only
			STATUS	current
			::= { hmWanMbus72 35 }

hmWanMbus72VIF0F		OBJECT-TYPE
			SYNTAX	INTEGER
			MAX-ACCESS	read-only
			STATUS	current
			::= { hmWanMbus72 36 }

hmWanMbus72Value0F		OBJECT-TYPE
			SYNTAX	INTEGER
			MAX-ACCESS	read-only
			STATUS	current
			::= { hmWanMbus72 37 }

hmWanMbus72VIF10		OBJECT-TYPE
			SYNTAX	INTEGER
			MAX-ACCESS	read-only
			STATUS	current
			::= { hmWanMbus72 38 }

hmWanMbus72Value10		OBJECT-TYPE
			SYNTAX	INTEGER
			MAX-ACCESS	read-only
			STATUS	current
			::= { hmWanMbus72 39 }

hmWanMbus72VIF11		OBJECT-TYPE
			SYNTAX	INTEGER
			MAX-ACCESS	read-only
			STATUS	current
			::= { hmWanMbus72 40 }

hmWanMbus72Value11		OBJECT-TYPE
			SYNTAX	INTEGER
			MAX-ACCESS	read-only
			STATUS	current
			::= { hmWanMbus72 41 }

hmWanMbus72VIF12		OBJECT-TYPE
			SYNTAX	INTEGER
			MAX-ACCESS	read-only
			STATUS	current
			::= { hmWanMbus72 42 }

hmWanMbus72Value12		OBJECT-TYPE
			SYNTAX	INTEGER
			MAX-ACCESS	read-only
			STATUS	current
			::= { hmWanMbus72 43 }

hmWanMbus72VIF13		OBJECT-TYPE
			SYNTAX	INTEGER
			MAX-ACCESS	read-only
			STATUS	current
			::= { hmWanMbus72 44 }

hmWanMbus72Value13		OBJECT-TYPE
			SYNTAX	INTEGER
			MAX-ACCESS	read-only
			STATUS	current
			::= { hmWanMbus72 45 }

hmWanMbus72VIF14		OBJECT-TYPE
			SYNTAX	INTEGER
			MAX-ACCESS	read-only
			STATUS	current
			::= { hmWanMbus72 46 }

hmWanMbus72Value14		OBJECT-TYPE
			SYNTAX	INTEGER
			MAX-ACCESS	read-only
			STATUS	current
			::= { hmWanMbus72 47 }

hmWanMbus72VIF15		OBJECT-TYPE
			SYNTAX	INTEGER
			MAX-ACCESS	read-only
			STATUS	current
			::= { hmWanMbus72 48 }

hmWanMbus72Value15		OBJECT-TYPE
			SYNTAX	INTEGER
			MAX-ACCESS	read-only
			STATUS	current
			::= { hmWanMbus72 49 }

hmWanMbus72VIF16		OBJECT-TYPE
			SYNTAX	INTEGER
			MAX-ACCESS	read-only
			STATUS	current
			::= { hmWanMbus72 50 }

hmWanMbus72Value16		OBJECT-TYPE
			SYNTAX	INTEGER
			MAX-ACCESS	read-only
			STATUS	current
			::= { hmWanMbus72 51 }

hmWanMbus72VIF17		OBJECT-TYPE
			SYNTAX	INTEGER
			MAX-ACCESS	read-only
			STATUS	current
			::= { hmWanMbus72 52 }

hmWanMbus72Value17		OBJECT-TYPE
			SYNTAX	INTEGER
			MAX-ACCESS	read-only
			STATUS	current
			::= { hmWanMbus72 53 }

hmWanMbus72VIF18		OBJECT-TYPE
			SYNTAX	INTEGER
			MAX-ACCESS	read-only
			STATUS	current
			::= { hmWanMbus72 54 }

hmWanMbus72Value18		OBJECT-TYPE
			SYNTAX	INTEGER
			MAX-ACCESS	read-only
			STATUS	current
			::= { hmWanMbus72 55 }

hmWanMbus72VIF19		OBJECT-TYPE
			SYNTAX	INTEGER
			MAX-ACCESS	read-only
			STATUS	current
			::= { hmWanMbus72 56 }

hmWanMbus72Value19		OBJECT-TYPE
			SYNTAX	INTEGER
			MAX-ACCESS	read-only
			STATUS	current
			::= { hmWanMbus72 57 }

hmWanMbus72VIF1A		OBJECT-TYPE
			SYNTAX	INTEGER
			MAX-ACCESS	read-only
			STATUS	current
			::= { hmWanMbus72 58 }

hmWanMbus72Value1A		OBJECT-TYPE
			SYNTAX	INTEGER
			MAX-ACCESS	read-only
			STATUS	current
			::= { hmWanMbus72 59 }

hmWanMbus72VIF1B		OBJECT-TYPE
			SYNTAX	INTEGER
			MAX-ACCESS	read-only
			STATUS	current
			::= { hmWanMbus72 60 }

hmWanMbus72Value1B		OBJECT-TYPE
			SYNTAX	INTEGER
			MAX-ACCESS	read-only
			STATUS	current
			::= { hmWanMbus72 61 }

hmWanMbus72VIF1C		OBJECT-TYPE
			SYNTAX	INTEGER
			MAX-ACCESS	read-only
			STATUS	current
			::= { hmWanMbus72 62 }

hmWanMbus72Value1C		OBJECT-TYPE
			SYNTAX	INTEGER
			MAX-ACCESS	read-only
			STATUS	current
			::= { hmWanMbus72 63 }

hmWanMbus72VIF1D		OBJECT-TYPE
			SYNTAX	INTEGER
			MAX-ACCESS	read-only
			STATUS	current
			::= { hmWanMbus72 64 }

hmWanMbus72Value1D		OBJECT-TYPE
			SYNTAX	INTEGER
			MAX-ACCESS	read-only
			STATUS	current
			::= { hmWanMbus72 65 }

hmWanMbus72VIF1E		OBJECT-TYPE
			SYNTAX	INTEGER
			MAX-ACCESS	read-only
			STATUS	current
			::= { hmWanMbus72 66 }

hmWanMbus72Value1E		OBJECT-TYPE
			SYNTAX	INTEGER
			MAX-ACCESS	read-only
			STATUS	current
			::= { hmWanMbus72 67 }

hmWanMbus72VIF1F		OBJECT-TYPE
			SYNTAX	INTEGER
			MAX-ACCESS	read-only
			STATUS	current
			::= { hmWanMbus72 68 }

hmWanMbus72Value1F		OBJECT-TYPE
			SYNTAX	INTEGER
			MAX-ACCESS	read-only
			STATUS	current
			::= { hmWanMbus72 69 }

hmWanMbus72VIF20		OBJECT-TYPE
			SYNTAX	INTEGER
			MAX-ACCESS	read-only
			STATUS	current
			::= { hmWanMbus72 70 }

hmWanMbus72Value20		OBJECT-TYPE
			SYNTAX	INTEGER
			MAX-ACCESS	read-only
			STATUS	current
			::= { hmWanMbus72 71 }

hmWanMbus72VIF21		OBJECT-TYPE
			SYNTAX	INTEGER
			MAX-ACCESS	read-only
			STATUS	current
			::= { hmWanMbus72 72 }

hmWanMbus72Value21		OBJECT-TYPE
			SYNTAX	INTEGER
			MAX-ACCESS	read-only
			STATUS	current
			::= { hmWanMbus72 73 }

hmWanMbus72VIF22		OBJECT-TYPE
			SYNTAX	INTEGER
			MAX-ACCESS	read-only
			STATUS	current
			::= { hmWanMbus72 74 }

hmWanMbus72Value22		OBJECT-TYPE
			SYNTAX	INTEGER
			MAX-ACCESS	read-only
			STATUS	current
			::= { hmWanMbus72 75 }

hmWanMbus72VIF23		OBJECT-TYPE
			SYNTAX	INTEGER
			MAX-ACCESS	read-only
			STATUS	current
			::= { hmWanMbus72 76 }

hmWanMbus72Value23		OBJECT-TYPE
			SYNTAX	INTEGER
			MAX-ACCESS	read-only
			STATUS	current
			::= { hmWanMbus72 77 }

hmWanMbus72VIF24		OBJECT-TYPE
			SYNTAX	INTEGER
			MAX-ACCESS	read-only
			STATUS	current
			::= { hmWanMbus72 78 }

hmWanMbus72Value24		OBJECT-TYPE
			SYNTAX	INTEGER
			MAX-ACCESS	read-only
			STATUS	current
			::= { hmWanMbus72 79 }

hmWanMbus72VIF25		OBJECT-TYPE
			SYNTAX	INTEGER
			MAX-ACCESS	read-only
			STATUS	current
			::= { hmWanMbus72 80 }

hmWanMbus72Value25		OBJECT-TYPE
			SYNTAX	INTEGER
			MAX-ACCESS	read-only
			STATUS	current
			::= { hmWanMbus72 81 }

hmWanMbus72VIF26		OBJECT-TYPE
			SYNTAX	INTEGER
			MAX-ACCESS	read-only
			STATUS	current
			::= { hmWanMbus72 82 }

hmWanMbus72Value26		OBJECT-TYPE
			SYNTAX	INTEGER
			MAX-ACCESS	read-only
			STATUS	current
			::= { hmWanMbus72 83 }

hmWanMbus72VIF27		OBJECT-TYPE
			SYNTAX	INTEGER
			MAX-ACCESS	read-only
			STATUS	current
			::= { hmWanMbus72 84 }

hmWanMbus72Value27		OBJECT-TYPE
			SYNTAX	INTEGER
			MAX-ACCESS	read-only
			STATUS	current
			::= { hmWanMbus72 85 }

hmWanMbus72VIF28		OBJECT-TYPE
			SYNTAX	INTEGER
			MAX-ACCESS	read-only
			STATUS	current
			::= { hmWanMbus72 86 }

hmWanMbus72Value28		OBJECT-TYPE
			SYNTAX	INTEGER
			MAX-ACCESS	read-only
			STATUS	current
			::= { hmWanMbus72 87 }

hmWanMbus72VIF29		OBJECT-TYPE
			SYNTAX	INTEGER
			MAX-ACCESS	read-only
			STATUS	current
			::= { hmWanMbus72 88 }

hmWanMbus72Value29		OBJECT-TYPE
			SYNTAX	INTEGER
			MAX-ACCESS	read-only
			STATUS	current
			::= { hmWanMbus72 89 }

hmWanMbus72VIF2A		OBJECT-TYPE
			SYNTAX	INTEGER
			MAX-ACCESS	read-only
			STATUS	current
			::= { hmWanMbus72 90 }

hmWanMbus72Value2A		OBJECT-TYPE
			SYNTAX	INTEGER
			MAX-ACCESS	read-only
			STATUS	current
			::= { hmWanMbus72 91 }

hmWanMbus72VIF2B		OBJECT-TYPE
			SYNTAX	INTEGER
			MAX-ACCESS	read-only
			STATUS	current
			::= { hmWanMbus72 92 }

hmWanMbus72Value2B		OBJECT-TYPE
			SYNTAX	INTEGER
			MAX-ACCESS	read-only
			STATUS	current
			::= { hmWanMbus72 93 }

hmWanMbus72VIF2C		OBJECT-TYPE
			SYNTAX	INTEGER
			MAX-ACCESS	read-only
			STATUS	current
			::= { hmWanMbus72 94 }

hmWanMbus72Value2C		OBJECT-TYPE
			SYNTAX	INTEGER
			MAX-ACCESS	read-only
			STATUS	current
			::= { hmWanMbus72 95 }

hmWanMbus72VIF2D		OBJECT-TYPE
			SYNTAX	INTEGER
			MAX-ACCESS	read-only
			STATUS	current
			::= { hmWanMbus72 96 }

hmWanMbus72Value2D		OBJECT-TYPE
			SYNTAX	INTEGER
			MAX-ACCESS	read-only
			STATUS	current
			::= { hmWanMbus72 97 }

hmWanMbus72VIF2E		OBJECT-TYPE
			SYNTAX	INTEGER
			MAX-ACCESS	read-only
			STATUS	current
			::= { hmWanMbus72 98 }

hmWanMbus72Value2E		OBJECT-TYPE
			SYNTAX	INTEGER
			MAX-ACCESS	read-only
			STATUS	current
			::= { hmWanMbus72 99 }

hmWanMbus72VIF2F		OBJECT-TYPE
			SYNTAX	INTEGER
			MAX-ACCESS	read-only
			STATUS	current
			::= { hmWanMbus72 100 }

hmWanMbus72Value2F		OBJECT-TYPE
			SYNTAX	INTEGER
			MAX-ACCESS	read-only
			STATUS	current
			::= { hmWanMbus72 101 }

hmWanMbus73			OBJECT IDENTIFIER ::= { hmWanMbus 115 }

hmWanMbus73IdNumber		OBJECT-TYPE
			SYNTAX	Gauge32
			MAX-ACCESS	read-only
			STATUS	current
			::= { hmWanMbus73 1 }

hmWanMbus73Manufacturer	OBJECT-TYPE
			SYNTAX	Gauge32
			MAX-ACCESS	read-only
			STATUS	current
			::= { hmWanMbus73 2 }

hmWanMbus73Version		OBJECT-TYPE
			SYNTAX	Gauge32
			MAX-ACCESS	read-only
			STATUS	current
			::= { hmWanMbus73 3 }

hmWanMbus73Medium		OBJECT-TYPE
			SYNTAX	Gauge32
			MAX-ACCESS	read-only
			STATUS	current
			::= { hmWanMbus73 4 }

hmWanMbus73Status		OBJECT-TYPE
			SYNTAX	Gauge32
			MAX-ACCESS	read-only
			STATUS	current
			::= { hmWanMbus73 5 }

hmWanMbus73VIF00		OBJECT-TYPE
			SYNTAX	INTEGER
			MAX-ACCESS	read-only
			STATUS	current
			::= { hmWanMbus73 6 }

hmWanMbus73Value00		OBJECT-TYPE
			SYNTAX	INTEGER
			MAX-ACCESS	read-only
			STATUS	current
			::= { hmWanMbus73 7 }

hmWanMbus73VIF01		OBJECT-TYPE
			SYNTAX	INTEGER
			MAX-ACCESS	read-only
			STATUS	current
			::= { hmWanMbus73 8 }

hmWanMbus73Value01		OBJECT-TYPE
			SYNTAX	INTEGER
			MAX-ACCESS	read-only
			STATUS	current
			::= { hmWanMbus73 9 }

hmWanMbus73VIF02		OBJECT-TYPE
			SYNTAX	INTEGER
			MAX-ACCESS	read-only
			STATUS	current
			::= { hmWanMbus73 10 }

hmWanMbus73Value02		OBJECT-TYPE
			SYNTAX	INTEGER
			MAX-ACCESS	read-only
			STATUS	current
			::= { hmWanMbus73 11 }

hmWanMbus73VIF03		OBJECT-TYPE
			SYNTAX	INTEGER
			MAX-ACCESS	read-only
			STATUS	current
			::= { hmWanMbus73 12 }

hmWanMbus73Value03		OBJECT-TYPE
			SYNTAX	INTEGER
			MAX-ACCESS	read-only
			STATUS	current
			::= { hmWanMbus73 13 }

hmWanMbus73VIF04		OBJECT-TYPE
			SYNTAX	INTEGER
			MAX-ACCESS	read-only
			STATUS	current
			::= { hmWanMbus73 14 }

hmWanMbus73Value04		OBJECT-TYPE
			SYNTAX	INTEGER
			MAX-ACCESS	read-only
			STATUS	current
			::= { hmWanMbus73 15 }

hmWanMbus73VIF05		OBJECT-TYPE
			SYNTAX	INTEGER
			MAX-ACCESS	read-only
			STATUS	current
			::= { hmWanMbus73 16 }

hmWanMbus73Value05		OBJECT-TYPE
			SYNTAX	INTEGER
			MAX-ACCESS	read-only
			STATUS	current
			::= { hmWanMbus73 17 }

hmWanMbus73VIF06		OBJECT-TYPE
			SYNTAX	INTEGER
			MAX-ACCESS	read-only
			STATUS	current
			::= { hmWanMbus73 18 }

hmWanMbus73Value06		OBJECT-TYPE
			SYNTAX	INTEGER
			MAX-ACCESS	read-only
			STATUS	current
			::= { hmWanMbus73 19 }

hmWanMbus73VIF07		OBJECT-TYPE
			SYNTAX	INTEGER
			MAX-ACCESS	read-only
			STATUS	current
			::= { hmWanMbus73 20 }

hmWanMbus73Value07		OBJECT-TYPE
			SYNTAX	INTEGER
			MAX-ACCESS	read-only
			STATUS	current
			::= { hmWanMbus73 21 }

hmWanMbus73VIF08		OBJECT-TYPE
			SYNTAX	INTEGER
			MAX-ACCESS	read-only
			STATUS	current
			::= { hmWanMbus73 22 }

hmWanMbus73Value08		OBJECT-TYPE
			SYNTAX	INTEGER
			MAX-ACCESS	read-only
			STATUS	current
			::= { hmWanMbus73 23 }

hmWanMbus73VIF09		OBJECT-TYPE
			SYNTAX	INTEGER
			MAX-ACCESS	read-only
			STATUS	current
			::= { hmWanMbus73 24 }

hmWanMbus73Value09		OBJECT-TYPE
			SYNTAX	INTEGER
			MAX-ACCESS	read-only
			STATUS	current
			::= { hmWanMbus73 25 }

hmWanMbus73VIF0A		OBJECT-TYPE
			SYNTAX	INTEGER
			MAX-ACCESS	read-only
			STATUS	current
			::= { hmWanMbus73 26 }

hmWanMbus73Value0A		OBJECT-TYPE
			SYNTAX	INTEGER
			MAX-ACCESS	read-only
			STATUS	current
			::= { hmWanMbus73 27 }

hmWanMbus73VIF0B		OBJECT-TYPE
			SYNTAX	INTEGER
			MAX-ACCESS	read-only
			STATUS	current
			::= { hmWanMbus73 28 }

hmWanMbus73Value0B		OBJECT-TYPE
			SYNTAX	INTEGER
			MAX-ACCESS	read-only
			STATUS	current
			::= { hmWanMbus73 29 }

hmWanMbus73VIF0C		OBJECT-TYPE
			SYNTAX	INTEGER
			MAX-ACCESS	read-only
			STATUS	current
			::= { hmWanMbus73 30 }

hmWanMbus73Value0C		OBJECT-TYPE
			SYNTAX	INTEGER
			MAX-ACCESS	read-only
			STATUS	current
			::= { hmWanMbus73 31 }

hmWanMbus73VIF0D		OBJECT-TYPE
			SYNTAX	INTEGER
			MAX-ACCESS	read-only
			STATUS	current
			::= { hmWanMbus73 32 }

hmWanMbus73Value0D		OBJECT-TYPE
			SYNTAX	INTEGER
			MAX-ACCESS	read-only
			STATUS	current
			::= { hmWanMbus73 33 }

hmWanMbus73VIF0E		OBJECT-TYPE
			SYNTAX	INTEGER
			MAX-ACCESS	read-only
			STATUS	current
			::= { hmWanMbus73 34 }

hmWanMbus73Value0E		OBJECT-TYPE
			SYNTAX	INTEGER
			MAX-ACCESS	read-only
			STATUS	current
			::= { hmWanMbus73 35 }

hmWanMbus73VIF0F		OBJECT-TYPE
			SYNTAX	INTEGER
			MAX-ACCESS	read-only
			STATUS	current
			::= { hmWanMbus73 36 }

hmWanMbus73Value0F		OBJECT-TYPE
			SYNTAX	INTEGER
			MAX-ACCESS	read-only
			STATUS	current
			::= { hmWanMbus73 37 }

hmWanMbus73VIF10		OBJECT-TYPE
			SYNTAX	INTEGER
			MAX-ACCESS	read-only
			STATUS	current
			::= { hmWanMbus73 38 }

hmWanMbus73Value10		OBJECT-TYPE
			SYNTAX	INTEGER
			MAX-ACCESS	read-only
			STATUS	current
			::= { hmWanMbus73 39 }

hmWanMbus73VIF11		OBJECT-TYPE
			SYNTAX	INTEGER
			MAX-ACCESS	read-only
			STATUS	current
			::= { hmWanMbus73 40 }

hmWanMbus73Value11		OBJECT-TYPE
			SYNTAX	INTEGER
			MAX-ACCESS	read-only
			STATUS	current
			::= { hmWanMbus73 41 }

hmWanMbus73VIF12		OBJECT-TYPE
			SYNTAX	INTEGER
			MAX-ACCESS	read-only
			STATUS	current
			::= { hmWanMbus73 42 }

hmWanMbus73Value12		OBJECT-TYPE
			SYNTAX	INTEGER
			MAX-ACCESS	read-only
			STATUS	current
			::= { hmWanMbus73 43 }

hmWanMbus73VIF13		OBJECT-TYPE
			SYNTAX	INTEGER
			MAX-ACCESS	read-only
			STATUS	current
			::= { hmWanMbus73 44 }

hmWanMbus73Value13		OBJECT-TYPE
			SYNTAX	INTEGER
			MAX-ACCESS	read-only
			STATUS	current
			::= { hmWanMbus73 45 }

hmWanMbus73VIF14		OBJECT-TYPE
			SYNTAX	INTEGER
			MAX-ACCESS	read-only
			STATUS	current
			::= { hmWanMbus73 46 }

hmWanMbus73Value14		OBJECT-TYPE
			SYNTAX	INTEGER
			MAX-ACCESS	read-only
			STATUS	current
			::= { hmWanMbus73 47 }

hmWanMbus73VIF15		OBJECT-TYPE
			SYNTAX	INTEGER
			MAX-ACCESS	read-only
			STATUS	current
			::= { hmWanMbus73 48 }

hmWanMbus73Value15		OBJECT-TYPE
			SYNTAX	INTEGER
			MAX-ACCESS	read-only
			STATUS	current
			::= { hmWanMbus73 49 }

hmWanMbus73VIF16		OBJECT-TYPE
			SYNTAX	INTEGER
			MAX-ACCESS	read-only
			STATUS	current
			::= { hmWanMbus73 50 }

hmWanMbus73Value16		OBJECT-TYPE
			SYNTAX	INTEGER
			MAX-ACCESS	read-only
			STATUS	current
			::= { hmWanMbus73 51 }

hmWanMbus73VIF17		OBJECT-TYPE
			SYNTAX	INTEGER
			MAX-ACCESS	read-only
			STATUS	current
			::= { hmWanMbus73 52 }

hmWanMbus73Value17		OBJECT-TYPE
			SYNTAX	INTEGER
			MAX-ACCESS	read-only
			STATUS	current
			::= { hmWanMbus73 53 }

hmWanMbus73VIF18		OBJECT-TYPE
			SYNTAX	INTEGER
			MAX-ACCESS	read-only
			STATUS	current
			::= { hmWanMbus73 54 }

hmWanMbus73Value18		OBJECT-TYPE
			SYNTAX	INTEGER
			MAX-ACCESS	read-only
			STATUS	current
			::= { hmWanMbus73 55 }

hmWanMbus73VIF19		OBJECT-TYPE
			SYNTAX	INTEGER
			MAX-ACCESS	read-only
			STATUS	current
			::= { hmWanMbus73 56 }

hmWanMbus73Value19		OBJECT-TYPE
			SYNTAX	INTEGER
			MAX-ACCESS	read-only
			STATUS	current
			::= { hmWanMbus73 57 }

hmWanMbus73VIF1A		OBJECT-TYPE
			SYNTAX	INTEGER
			MAX-ACCESS	read-only
			STATUS	current
			::= { hmWanMbus73 58 }

hmWanMbus73Value1A		OBJECT-TYPE
			SYNTAX	INTEGER
			MAX-ACCESS	read-only
			STATUS	current
			::= { hmWanMbus73 59 }

hmWanMbus73VIF1B		OBJECT-TYPE
			SYNTAX	INTEGER
			MAX-ACCESS	read-only
			STATUS	current
			::= { hmWanMbus73 60 }

hmWanMbus73Value1B		OBJECT-TYPE
			SYNTAX	INTEGER
			MAX-ACCESS	read-only
			STATUS	current
			::= { hmWanMbus73 61 }

hmWanMbus73VIF1C		OBJECT-TYPE
			SYNTAX	INTEGER
			MAX-ACCESS	read-only
			STATUS	current
			::= { hmWanMbus73 62 }

hmWanMbus73Value1C		OBJECT-TYPE
			SYNTAX	INTEGER
			MAX-ACCESS	read-only
			STATUS	current
			::= { hmWanMbus73 63 }

hmWanMbus73VIF1D		OBJECT-TYPE
			SYNTAX	INTEGER
			MAX-ACCESS	read-only
			STATUS	current
			::= { hmWanMbus73 64 }

hmWanMbus73Value1D		OBJECT-TYPE
			SYNTAX	INTEGER
			MAX-ACCESS	read-only
			STATUS	current
			::= { hmWanMbus73 65 }

hmWanMbus73VIF1E		OBJECT-TYPE
			SYNTAX	INTEGER
			MAX-ACCESS	read-only
			STATUS	current
			::= { hmWanMbus73 66 }

hmWanMbus73Value1E		OBJECT-TYPE
			SYNTAX	INTEGER
			MAX-ACCESS	read-only
			STATUS	current
			::= { hmWanMbus73 67 }

hmWanMbus73VIF1F		OBJECT-TYPE
			SYNTAX	INTEGER
			MAX-ACCESS	read-only
			STATUS	current
			::= { hmWanMbus73 68 }

hmWanMbus73Value1F		OBJECT-TYPE
			SYNTAX	INTEGER
			MAX-ACCESS	read-only
			STATUS	current
			::= { hmWanMbus73 69 }

hmWanMbus73VIF20		OBJECT-TYPE
			SYNTAX	INTEGER
			MAX-ACCESS	read-only
			STATUS	current
			::= { hmWanMbus73 70 }

hmWanMbus73Value20		OBJECT-TYPE
			SYNTAX	INTEGER
			MAX-ACCESS	read-only
			STATUS	current
			::= { hmWanMbus73 71 }

hmWanMbus73VIF21		OBJECT-TYPE
			SYNTAX	INTEGER
			MAX-ACCESS	read-only
			STATUS	current
			::= { hmWanMbus73 72 }

hmWanMbus73Value21		OBJECT-TYPE
			SYNTAX	INTEGER
			MAX-ACCESS	read-only
			STATUS	current
			::= { hmWanMbus73 73 }

hmWanMbus73VIF22		OBJECT-TYPE
			SYNTAX	INTEGER
			MAX-ACCESS	read-only
			STATUS	current
			::= { hmWanMbus73 74 }

hmWanMbus73Value22		OBJECT-TYPE
			SYNTAX	INTEGER
			MAX-ACCESS	read-only
			STATUS	current
			::= { hmWanMbus73 75 }

hmWanMbus73VIF23		OBJECT-TYPE
			SYNTAX	INTEGER
			MAX-ACCESS	read-only
			STATUS	current
			::= { hmWanMbus73 76 }

hmWanMbus73Value23		OBJECT-TYPE
			SYNTAX	INTEGER
			MAX-ACCESS	read-only
			STATUS	current
			::= { hmWanMbus73 77 }

hmWanMbus73VIF24		OBJECT-TYPE
			SYNTAX	INTEGER
			MAX-ACCESS	read-only
			STATUS	current
			::= { hmWanMbus73 78 }

hmWanMbus73Value24		OBJECT-TYPE
			SYNTAX	INTEGER
			MAX-ACCESS	read-only
			STATUS	current
			::= { hmWanMbus73 79 }

hmWanMbus73VIF25		OBJECT-TYPE
			SYNTAX	INTEGER
			MAX-ACCESS	read-only
			STATUS	current
			::= { hmWanMbus73 80 }

hmWanMbus73Value25		OBJECT-TYPE
			SYNTAX	INTEGER
			MAX-ACCESS	read-only
			STATUS	current
			::= { hmWanMbus73 81 }

hmWanMbus73VIF26		OBJECT-TYPE
			SYNTAX	INTEGER
			MAX-ACCESS	read-only
			STATUS	current
			::= { hmWanMbus73 82 }

hmWanMbus73Value26		OBJECT-TYPE
			SYNTAX	INTEGER
			MAX-ACCESS	read-only
			STATUS	current
			::= { hmWanMbus73 83 }

hmWanMbus73VIF27		OBJECT-TYPE
			SYNTAX	INTEGER
			MAX-ACCESS	read-only
			STATUS	current
			::= { hmWanMbus73 84 }

hmWanMbus73Value27		OBJECT-TYPE
			SYNTAX	INTEGER
			MAX-ACCESS	read-only
			STATUS	current
			::= { hmWanMbus73 85 }

hmWanMbus73VIF28		OBJECT-TYPE
			SYNTAX	INTEGER
			MAX-ACCESS	read-only
			STATUS	current
			::= { hmWanMbus73 86 }

hmWanMbus73Value28		OBJECT-TYPE
			SYNTAX	INTEGER
			MAX-ACCESS	read-only
			STATUS	current
			::= { hmWanMbus73 87 }

hmWanMbus73VIF29		OBJECT-TYPE
			SYNTAX	INTEGER
			MAX-ACCESS	read-only
			STATUS	current
			::= { hmWanMbus73 88 }

hmWanMbus73Value29		OBJECT-TYPE
			SYNTAX	INTEGER
			MAX-ACCESS	read-only
			STATUS	current
			::= { hmWanMbus73 89 }

hmWanMbus73VIF2A		OBJECT-TYPE
			SYNTAX	INTEGER
			MAX-ACCESS	read-only
			STATUS	current
			::= { hmWanMbus73 90 }

hmWanMbus73Value2A		OBJECT-TYPE
			SYNTAX	INTEGER
			MAX-ACCESS	read-only
			STATUS	current
			::= { hmWanMbus73 91 }

hmWanMbus73VIF2B		OBJECT-TYPE
			SYNTAX	INTEGER
			MAX-ACCESS	read-only
			STATUS	current
			::= { hmWanMbus73 92 }

hmWanMbus73Value2B		OBJECT-TYPE
			SYNTAX	INTEGER
			MAX-ACCESS	read-only
			STATUS	current
			::= { hmWanMbus73 93 }

hmWanMbus73VIF2C		OBJECT-TYPE
			SYNTAX	INTEGER
			MAX-ACCESS	read-only
			STATUS	current
			::= { hmWanMbus73 94 }

hmWanMbus73Value2C		OBJECT-TYPE
			SYNTAX	INTEGER
			MAX-ACCESS	read-only
			STATUS	current
			::= { hmWanMbus73 95 }

hmWanMbus73VIF2D		OBJECT-TYPE
			SYNTAX	INTEGER
			MAX-ACCESS	read-only
			STATUS	current
			::= { hmWanMbus73 96 }

hmWanMbus73Value2D		OBJECT-TYPE
			SYNTAX	INTEGER
			MAX-ACCESS	read-only
			STATUS	current
			::= { hmWanMbus73 97 }

hmWanMbus73VIF2E		OBJECT-TYPE
			SYNTAX	INTEGER
			MAX-ACCESS	read-only
			STATUS	current
			::= { hmWanMbus73 98 }

hmWanMbus73Value2E		OBJECT-TYPE
			SYNTAX	INTEGER
			MAX-ACCESS	read-only
			STATUS	current
			::= { hmWanMbus73 99 }

hmWanMbus73VIF2F		OBJECT-TYPE
			SYNTAX	INTEGER
			MAX-ACCESS	read-only
			STATUS	current
			::= { hmWanMbus73 100 }

hmWanMbus73Value2F		OBJECT-TYPE
			SYNTAX	INTEGER
			MAX-ACCESS	read-only
			STATUS	current
			::= { hmWanMbus73 101 }

hmWanMbus74			OBJECT IDENTIFIER ::= { hmWanMbus 116 }

hmWanMbus74IdNumber		OBJECT-TYPE
			SYNTAX	Gauge32
			MAX-ACCESS	read-only
			STATUS	current
			::= { hmWanMbus74 1 }

hmWanMbus74Manufacturer	OBJECT-TYPE
			SYNTAX	Gauge32
			MAX-ACCESS	read-only
			STATUS	current
			::= { hmWanMbus74 2 }

hmWanMbus74Version		OBJECT-TYPE
			SYNTAX	Gauge32
			MAX-ACCESS	read-only
			STATUS	current
			::= { hmWanMbus74 3 }

hmWanMbus74Medium		OBJECT-TYPE
			SYNTAX	Gauge32
			MAX-ACCESS	read-only
			STATUS	current
			::= { hmWanMbus74 4 }

hmWanMbus74Status		OBJECT-TYPE
			SYNTAX	Gauge32
			MAX-ACCESS	read-only
			STATUS	current
			::= { hmWanMbus74 5 }

hmWanMbus74VIF00		OBJECT-TYPE
			SYNTAX	INTEGER
			MAX-ACCESS	read-only
			STATUS	current
			::= { hmWanMbus74 6 }

hmWanMbus74Value00		OBJECT-TYPE
			SYNTAX	INTEGER
			MAX-ACCESS	read-only
			STATUS	current
			::= { hmWanMbus74 7 }

hmWanMbus74VIF01		OBJECT-TYPE
			SYNTAX	INTEGER
			MAX-ACCESS	read-only
			STATUS	current
			::= { hmWanMbus74 8 }

hmWanMbus74Value01		OBJECT-TYPE
			SYNTAX	INTEGER
			MAX-ACCESS	read-only
			STATUS	current
			::= { hmWanMbus74 9 }

hmWanMbus74VIF02		OBJECT-TYPE
			SYNTAX	INTEGER
			MAX-ACCESS	read-only
			STATUS	current
			::= { hmWanMbus74 10 }

hmWanMbus74Value02		OBJECT-TYPE
			SYNTAX	INTEGER
			MAX-ACCESS	read-only
			STATUS	current
			::= { hmWanMbus74 11 }

hmWanMbus74VIF03		OBJECT-TYPE
			SYNTAX	INTEGER
			MAX-ACCESS	read-only
			STATUS	current
			::= { hmWanMbus74 12 }

hmWanMbus74Value03		OBJECT-TYPE
			SYNTAX	INTEGER
			MAX-ACCESS	read-only
			STATUS	current
			::= { hmWanMbus74 13 }

hmWanMbus74VIF04		OBJECT-TYPE
			SYNTAX	INTEGER
			MAX-ACCESS	read-only
			STATUS	current
			::= { hmWanMbus74 14 }

hmWanMbus74Value04		OBJECT-TYPE
			SYNTAX	INTEGER
			MAX-ACCESS	read-only
			STATUS	current
			::= { hmWanMbus74 15 }

hmWanMbus74VIF05		OBJECT-TYPE
			SYNTAX	INTEGER
			MAX-ACCESS	read-only
			STATUS	current
			::= { hmWanMbus74 16 }

hmWanMbus74Value05		OBJECT-TYPE
			SYNTAX	INTEGER
			MAX-ACCESS	read-only
			STATUS	current
			::= { hmWanMbus74 17 }

hmWanMbus74VIF06		OBJECT-TYPE
			SYNTAX	INTEGER
			MAX-ACCESS	read-only
			STATUS	current
			::= { hmWanMbus74 18 }

hmWanMbus74Value06		OBJECT-TYPE
			SYNTAX	INTEGER
			MAX-ACCESS	read-only
			STATUS	current
			::= { hmWanMbus74 19 }

hmWanMbus74VIF07		OBJECT-TYPE
			SYNTAX	INTEGER
			MAX-ACCESS	read-only
			STATUS	current
			::= { hmWanMbus74 20 }

hmWanMbus74Value07		OBJECT-TYPE
			SYNTAX	INTEGER
			MAX-ACCESS	read-only
			STATUS	current
			::= { hmWanMbus74 21 }

hmWanMbus74VIF08		OBJECT-TYPE
			SYNTAX	INTEGER
			MAX-ACCESS	read-only
			STATUS	current
			::= { hmWanMbus74 22 }

hmWanMbus74Value08		OBJECT-TYPE
			SYNTAX	INTEGER
			MAX-ACCESS	read-only
			STATUS	current
			::= { hmWanMbus74 23 }

hmWanMbus74VIF09		OBJECT-TYPE
			SYNTAX	INTEGER
			MAX-ACCESS	read-only
			STATUS	current
			::= { hmWanMbus74 24 }

hmWanMbus74Value09		OBJECT-TYPE
			SYNTAX	INTEGER
			MAX-ACCESS	read-only
			STATUS	current
			::= { hmWanMbus74 25 }

hmWanMbus74VIF0A		OBJECT-TYPE
			SYNTAX	INTEGER
			MAX-ACCESS	read-only
			STATUS	current
			::= { hmWanMbus74 26 }

hmWanMbus74Value0A		OBJECT-TYPE
			SYNTAX	INTEGER
			MAX-ACCESS	read-only
			STATUS	current
			::= { hmWanMbus74 27 }

hmWanMbus74VIF0B		OBJECT-TYPE
			SYNTAX	INTEGER
			MAX-ACCESS	read-only
			STATUS	current
			::= { hmWanMbus74 28 }

hmWanMbus74Value0B		OBJECT-TYPE
			SYNTAX	INTEGER
			MAX-ACCESS	read-only
			STATUS	current
			::= { hmWanMbus74 29 }

hmWanMbus74VIF0C		OBJECT-TYPE
			SYNTAX	INTEGER
			MAX-ACCESS	read-only
			STATUS	current
			::= { hmWanMbus74 30 }

hmWanMbus74Value0C		OBJECT-TYPE
			SYNTAX	INTEGER
			MAX-ACCESS	read-only
			STATUS	current
			::= { hmWanMbus74 31 }

hmWanMbus74VIF0D		OBJECT-TYPE
			SYNTAX	INTEGER
			MAX-ACCESS	read-only
			STATUS	current
			::= { hmWanMbus74 32 }

hmWanMbus74Value0D		OBJECT-TYPE
			SYNTAX	INTEGER
			MAX-ACCESS	read-only
			STATUS	current
			::= { hmWanMbus74 33 }

hmWanMbus74VIF0E		OBJECT-TYPE
			SYNTAX	INTEGER
			MAX-ACCESS	read-only
			STATUS	current
			::= { hmWanMbus74 34 }

hmWanMbus74Value0E		OBJECT-TYPE
			SYNTAX	INTEGER
			MAX-ACCESS	read-only
			STATUS	current
			::= { hmWanMbus74 35 }

hmWanMbus74VIF0F		OBJECT-TYPE
			SYNTAX	INTEGER
			MAX-ACCESS	read-only
			STATUS	current
			::= { hmWanMbus74 36 }

hmWanMbus74Value0F		OBJECT-TYPE
			SYNTAX	INTEGER
			MAX-ACCESS	read-only
			STATUS	current
			::= { hmWanMbus74 37 }

hmWanMbus74VIF10		OBJECT-TYPE
			SYNTAX	INTEGER
			MAX-ACCESS	read-only
			STATUS	current
			::= { hmWanMbus74 38 }

hmWanMbus74Value10		OBJECT-TYPE
			SYNTAX	INTEGER
			MAX-ACCESS	read-only
			STATUS	current
			::= { hmWanMbus74 39 }

hmWanMbus74VIF11		OBJECT-TYPE
			SYNTAX	INTEGER
			MAX-ACCESS	read-only
			STATUS	current
			::= { hmWanMbus74 40 }

hmWanMbus74Value11		OBJECT-TYPE
			SYNTAX	INTEGER
			MAX-ACCESS	read-only
			STATUS	current
			::= { hmWanMbus74 41 }

hmWanMbus74VIF12		OBJECT-TYPE
			SYNTAX	INTEGER
			MAX-ACCESS	read-only
			STATUS	current
			::= { hmWanMbus74 42 }

hmWanMbus74Value12		OBJECT-TYPE
			SYNTAX	INTEGER
			MAX-ACCESS	read-only
			STATUS	current
			::= { hmWanMbus74 43 }

hmWanMbus74VIF13		OBJECT-TYPE
			SYNTAX	INTEGER
			MAX-ACCESS	read-only
			STATUS	current
			::= { hmWanMbus74 44 }

hmWanMbus74Value13		OBJECT-TYPE
			SYNTAX	INTEGER
			MAX-ACCESS	read-only
			STATUS	current
			::= { hmWanMbus74 45 }

hmWanMbus74VIF14		OBJECT-TYPE
			SYNTAX	INTEGER
			MAX-ACCESS	read-only
			STATUS	current
			::= { hmWanMbus74 46 }

hmWanMbus74Value14		OBJECT-TYPE
			SYNTAX	INTEGER
			MAX-ACCESS	read-only
			STATUS	current
			::= { hmWanMbus74 47 }

hmWanMbus74VIF15		OBJECT-TYPE
			SYNTAX	INTEGER
			MAX-ACCESS	read-only
			STATUS	current
			::= { hmWanMbus74 48 }

hmWanMbus74Value15		OBJECT-TYPE
			SYNTAX	INTEGER
			MAX-ACCESS	read-only
			STATUS	current
			::= { hmWanMbus74 49 }

hmWanMbus74VIF16		OBJECT-TYPE
			SYNTAX	INTEGER
			MAX-ACCESS	read-only
			STATUS	current
			::= { hmWanMbus74 50 }

hmWanMbus74Value16		OBJECT-TYPE
			SYNTAX	INTEGER
			MAX-ACCESS	read-only
			STATUS	current
			::= { hmWanMbus74 51 }

hmWanMbus74VIF17		OBJECT-TYPE
			SYNTAX	INTEGER
			MAX-ACCESS	read-only
			STATUS	current
			::= { hmWanMbus74 52 }

hmWanMbus74Value17		OBJECT-TYPE
			SYNTAX	INTEGER
			MAX-ACCESS	read-only
			STATUS	current
			::= { hmWanMbus74 53 }

hmWanMbus74VIF18		OBJECT-TYPE
			SYNTAX	INTEGER
			MAX-ACCESS	read-only
			STATUS	current
			::= { hmWanMbus74 54 }

hmWanMbus74Value18		OBJECT-TYPE
			SYNTAX	INTEGER
			MAX-ACCESS	read-only
			STATUS	current
			::= { hmWanMbus74 55 }

hmWanMbus74VIF19		OBJECT-TYPE
			SYNTAX	INTEGER
			MAX-ACCESS	read-only
			STATUS	current
			::= { hmWanMbus74 56 }

hmWanMbus74Value19		OBJECT-TYPE
			SYNTAX	INTEGER
			MAX-ACCESS	read-only
			STATUS	current
			::= { hmWanMbus74 57 }

hmWanMbus74VIF1A		OBJECT-TYPE
			SYNTAX	INTEGER
			MAX-ACCESS	read-only
			STATUS	current
			::= { hmWanMbus74 58 }

hmWanMbus74Value1A		OBJECT-TYPE
			SYNTAX	INTEGER
			MAX-ACCESS	read-only
			STATUS	current
			::= { hmWanMbus74 59 }

hmWanMbus74VIF1B		OBJECT-TYPE
			SYNTAX	INTEGER
			MAX-ACCESS	read-only
			STATUS	current
			::= { hmWanMbus74 60 }

hmWanMbus74Value1B		OBJECT-TYPE
			SYNTAX	INTEGER
			MAX-ACCESS	read-only
			STATUS	current
			::= { hmWanMbus74 61 }

hmWanMbus74VIF1C		OBJECT-TYPE
			SYNTAX	INTEGER
			MAX-ACCESS	read-only
			STATUS	current
			::= { hmWanMbus74 62 }

hmWanMbus74Value1C		OBJECT-TYPE
			SYNTAX	INTEGER
			MAX-ACCESS	read-only
			STATUS	current
			::= { hmWanMbus74 63 }

hmWanMbus74VIF1D		OBJECT-TYPE
			SYNTAX	INTEGER
			MAX-ACCESS	read-only
			STATUS	current
			::= { hmWanMbus74 64 }

hmWanMbus74Value1D		OBJECT-TYPE
			SYNTAX	INTEGER
			MAX-ACCESS	read-only
			STATUS	current
			::= { hmWanMbus74 65 }

hmWanMbus74VIF1E		OBJECT-TYPE
			SYNTAX	INTEGER
			MAX-ACCESS	read-only
			STATUS	current
			::= { hmWanMbus74 66 }

hmWanMbus74Value1E		OBJECT-TYPE
			SYNTAX	INTEGER
			MAX-ACCESS	read-only
			STATUS	current
			::= { hmWanMbus74 67 }

hmWanMbus74VIF1F		OBJECT-TYPE
			SYNTAX	INTEGER
			MAX-ACCESS	read-only
			STATUS	current
			::= { hmWanMbus74 68 }

hmWanMbus74Value1F		OBJECT-TYPE
			SYNTAX	INTEGER
			MAX-ACCESS	read-only
			STATUS	current
			::= { hmWanMbus74 69 }

hmWanMbus74VIF20		OBJECT-TYPE
			SYNTAX	INTEGER
			MAX-ACCESS	read-only
			STATUS	current
			::= { hmWanMbus74 70 }

hmWanMbus74Value20		OBJECT-TYPE
			SYNTAX	INTEGER
			MAX-ACCESS	read-only
			STATUS	current
			::= { hmWanMbus74 71 }

hmWanMbus74VIF21		OBJECT-TYPE
			SYNTAX	INTEGER
			MAX-ACCESS	read-only
			STATUS	current
			::= { hmWanMbus74 72 }

hmWanMbus74Value21		OBJECT-TYPE
			SYNTAX	INTEGER
			MAX-ACCESS	read-only
			STATUS	current
			::= { hmWanMbus74 73 }

hmWanMbus74VIF22		OBJECT-TYPE
			SYNTAX	INTEGER
			MAX-ACCESS	read-only
			STATUS	current
			::= { hmWanMbus74 74 }

hmWanMbus74Value22		OBJECT-TYPE
			SYNTAX	INTEGER
			MAX-ACCESS	read-only
			STATUS	current
			::= { hmWanMbus74 75 }

hmWanMbus74VIF23		OBJECT-TYPE
			SYNTAX	INTEGER
			MAX-ACCESS	read-only
			STATUS	current
			::= { hmWanMbus74 76 }

hmWanMbus74Value23		OBJECT-TYPE
			SYNTAX	INTEGER
			MAX-ACCESS	read-only
			STATUS	current
			::= { hmWanMbus74 77 }

hmWanMbus74VIF24		OBJECT-TYPE
			SYNTAX	INTEGER
			MAX-ACCESS	read-only
			STATUS	current
			::= { hmWanMbus74 78 }

hmWanMbus74Value24		OBJECT-TYPE
			SYNTAX	INTEGER
			MAX-ACCESS	read-only
			STATUS	current
			::= { hmWanMbus74 79 }

hmWanMbus74VIF25		OBJECT-TYPE
			SYNTAX	INTEGER
			MAX-ACCESS	read-only
			STATUS	current
			::= { hmWanMbus74 80 }

hmWanMbus74Value25		OBJECT-TYPE
			SYNTAX	INTEGER
			MAX-ACCESS	read-only
			STATUS	current
			::= { hmWanMbus74 81 }

hmWanMbus74VIF26		OBJECT-TYPE
			SYNTAX	INTEGER
			MAX-ACCESS	read-only
			STATUS	current
			::= { hmWanMbus74 82 }

hmWanMbus74Value26		OBJECT-TYPE
			SYNTAX	INTEGER
			MAX-ACCESS	read-only
			STATUS	current
			::= { hmWanMbus74 83 }

hmWanMbus74VIF27		OBJECT-TYPE
			SYNTAX	INTEGER
			MAX-ACCESS	read-only
			STATUS	current
			::= { hmWanMbus74 84 }

hmWanMbus74Value27		OBJECT-TYPE
			SYNTAX	INTEGER
			MAX-ACCESS	read-only
			STATUS	current
			::= { hmWanMbus74 85 }

hmWanMbus74VIF28		OBJECT-TYPE
			SYNTAX	INTEGER
			MAX-ACCESS	read-only
			STATUS	current
			::= { hmWanMbus74 86 }

hmWanMbus74Value28		OBJECT-TYPE
			SYNTAX	INTEGER
			MAX-ACCESS	read-only
			STATUS	current
			::= { hmWanMbus74 87 }

hmWanMbus74VIF29		OBJECT-TYPE
			SYNTAX	INTEGER
			MAX-ACCESS	read-only
			STATUS	current
			::= { hmWanMbus74 88 }

hmWanMbus74Value29		OBJECT-TYPE
			SYNTAX	INTEGER
			MAX-ACCESS	read-only
			STATUS	current
			::= { hmWanMbus74 89 }

hmWanMbus74VIF2A		OBJECT-TYPE
			SYNTAX	INTEGER
			MAX-ACCESS	read-only
			STATUS	current
			::= { hmWanMbus74 90 }

hmWanMbus74Value2A		OBJECT-TYPE
			SYNTAX	INTEGER
			MAX-ACCESS	read-only
			STATUS	current
			::= { hmWanMbus74 91 }

hmWanMbus74VIF2B		OBJECT-TYPE
			SYNTAX	INTEGER
			MAX-ACCESS	read-only
			STATUS	current
			::= { hmWanMbus74 92 }

hmWanMbus74Value2B		OBJECT-TYPE
			SYNTAX	INTEGER
			MAX-ACCESS	read-only
			STATUS	current
			::= { hmWanMbus74 93 }

hmWanMbus74VIF2C		OBJECT-TYPE
			SYNTAX	INTEGER
			MAX-ACCESS	read-only
			STATUS	current
			::= { hmWanMbus74 94 }

hmWanMbus74Value2C		OBJECT-TYPE
			SYNTAX	INTEGER
			MAX-ACCESS	read-only
			STATUS	current
			::= { hmWanMbus74 95 }

hmWanMbus74VIF2D		OBJECT-TYPE
			SYNTAX	INTEGER
			MAX-ACCESS	read-only
			STATUS	current
			::= { hmWanMbus74 96 }

hmWanMbus74Value2D		OBJECT-TYPE
			SYNTAX	INTEGER
			MAX-ACCESS	read-only
			STATUS	current
			::= { hmWanMbus74 97 }

hmWanMbus74VIF2E		OBJECT-TYPE
			SYNTAX	INTEGER
			MAX-ACCESS	read-only
			STATUS	current
			::= { hmWanMbus74 98 }

hmWanMbus74Value2E		OBJECT-TYPE
			SYNTAX	INTEGER
			MAX-ACCESS	read-only
			STATUS	current
			::= { hmWanMbus74 99 }

hmWanMbus74VIF2F		OBJECT-TYPE
			SYNTAX	INTEGER
			MAX-ACCESS	read-only
			STATUS	current
			::= { hmWanMbus74 100 }

hmWanMbus74Value2F		OBJECT-TYPE
			SYNTAX	INTEGER
			MAX-ACCESS	read-only
			STATUS	current
			::= { hmWanMbus74 101 }

hmWanMbus75			OBJECT IDENTIFIER ::= { hmWanMbus 117 }

hmWanMbus75IdNumber		OBJECT-TYPE
			SYNTAX	Gauge32
			MAX-ACCESS	read-only
			STATUS	current
			::= { hmWanMbus75 1 }

hmWanMbus75Manufacturer	OBJECT-TYPE
			SYNTAX	Gauge32
			MAX-ACCESS	read-only
			STATUS	current
			::= { hmWanMbus75 2 }

hmWanMbus75Version		OBJECT-TYPE
			SYNTAX	Gauge32
			MAX-ACCESS	read-only
			STATUS	current
			::= { hmWanMbus75 3 }

hmWanMbus75Medium		OBJECT-TYPE
			SYNTAX	Gauge32
			MAX-ACCESS	read-only
			STATUS	current
			::= { hmWanMbus75 4 }

hmWanMbus75Status		OBJECT-TYPE
			SYNTAX	Gauge32
			MAX-ACCESS	read-only
			STATUS	current
			::= { hmWanMbus75 5 }

hmWanMbus75VIF00		OBJECT-TYPE
			SYNTAX	INTEGER
			MAX-ACCESS	read-only
			STATUS	current
			::= { hmWanMbus75 6 }

hmWanMbus75Value00		OBJECT-TYPE
			SYNTAX	INTEGER
			MAX-ACCESS	read-only
			STATUS	current
			::= { hmWanMbus75 7 }

hmWanMbus75VIF01		OBJECT-TYPE
			SYNTAX	INTEGER
			MAX-ACCESS	read-only
			STATUS	current
			::= { hmWanMbus75 8 }

hmWanMbus75Value01		OBJECT-TYPE
			SYNTAX	INTEGER
			MAX-ACCESS	read-only
			STATUS	current
			::= { hmWanMbus75 9 }

hmWanMbus75VIF02		OBJECT-TYPE
			SYNTAX	INTEGER
			MAX-ACCESS	read-only
			STATUS	current
			::= { hmWanMbus75 10 }

hmWanMbus75Value02		OBJECT-TYPE
			SYNTAX	INTEGER
			MAX-ACCESS	read-only
			STATUS	current
			::= { hmWanMbus75 11 }

hmWanMbus75VIF03		OBJECT-TYPE
			SYNTAX	INTEGER
			MAX-ACCESS	read-only
			STATUS	current
			::= { hmWanMbus75 12 }

hmWanMbus75Value03		OBJECT-TYPE
			SYNTAX	INTEGER
			MAX-ACCESS	read-only
			STATUS	current
			::= { hmWanMbus75 13 }

hmWanMbus75VIF04		OBJECT-TYPE
			SYNTAX	INTEGER
			MAX-ACCESS	read-only
			STATUS	current
			::= { hmWanMbus75 14 }

hmWanMbus75Value04		OBJECT-TYPE
			SYNTAX	INTEGER
			MAX-ACCESS	read-only
			STATUS	current
			::= { hmWanMbus75 15 }

hmWanMbus75VIF05		OBJECT-TYPE
			SYNTAX	INTEGER
			MAX-ACCESS	read-only
			STATUS	current
			::= { hmWanMbus75 16 }

hmWanMbus75Value05		OBJECT-TYPE
			SYNTAX	INTEGER
			MAX-ACCESS	read-only
			STATUS	current
			::= { hmWanMbus75 17 }

hmWanMbus75VIF06		OBJECT-TYPE
			SYNTAX	INTEGER
			MAX-ACCESS	read-only
			STATUS	current
			::= { hmWanMbus75 18 }

hmWanMbus75Value06		OBJECT-TYPE
			SYNTAX	INTEGER
			MAX-ACCESS	read-only
			STATUS	current
			::= { hmWanMbus75 19 }

hmWanMbus75VIF07		OBJECT-TYPE
			SYNTAX	INTEGER
			MAX-ACCESS	read-only
			STATUS	current
			::= { hmWanMbus75 20 }

hmWanMbus75Value07		OBJECT-TYPE
			SYNTAX	INTEGER
			MAX-ACCESS	read-only
			STATUS	current
			::= { hmWanMbus75 21 }

hmWanMbus75VIF08		OBJECT-TYPE
			SYNTAX	INTEGER
			MAX-ACCESS	read-only
			STATUS	current
			::= { hmWanMbus75 22 }

hmWanMbus75Value08		OBJECT-TYPE
			SYNTAX	INTEGER
			MAX-ACCESS	read-only
			STATUS	current
			::= { hmWanMbus75 23 }

hmWanMbus75VIF09		OBJECT-TYPE
			SYNTAX	INTEGER
			MAX-ACCESS	read-only
			STATUS	current
			::= { hmWanMbus75 24 }

hmWanMbus75Value09		OBJECT-TYPE
			SYNTAX	INTEGER
			MAX-ACCESS	read-only
			STATUS	current
			::= { hmWanMbus75 25 }

hmWanMbus75VIF0A		OBJECT-TYPE
			SYNTAX	INTEGER
			MAX-ACCESS	read-only
			STATUS	current
			::= { hmWanMbus75 26 }

hmWanMbus75Value0A		OBJECT-TYPE
			SYNTAX	INTEGER
			MAX-ACCESS	read-only
			STATUS	current
			::= { hmWanMbus75 27 }

hmWanMbus75VIF0B		OBJECT-TYPE
			SYNTAX	INTEGER
			MAX-ACCESS	read-only
			STATUS	current
			::= { hmWanMbus75 28 }

hmWanMbus75Value0B		OBJECT-TYPE
			SYNTAX	INTEGER
			MAX-ACCESS	read-only
			STATUS	current
			::= { hmWanMbus75 29 }

hmWanMbus75VIF0C		OBJECT-TYPE
			SYNTAX	INTEGER
			MAX-ACCESS	read-only
			STATUS	current
			::= { hmWanMbus75 30 }

hmWanMbus75Value0C		OBJECT-TYPE
			SYNTAX	INTEGER
			MAX-ACCESS	read-only
			STATUS	current
			::= { hmWanMbus75 31 }

hmWanMbus75VIF0D		OBJECT-TYPE
			SYNTAX	INTEGER
			MAX-ACCESS	read-only
			STATUS	current
			::= { hmWanMbus75 32 }

hmWanMbus75Value0D		OBJECT-TYPE
			SYNTAX	INTEGER
			MAX-ACCESS	read-only
			STATUS	current
			::= { hmWanMbus75 33 }

hmWanMbus75VIF0E		OBJECT-TYPE
			SYNTAX	INTEGER
			MAX-ACCESS	read-only
			STATUS	current
			::= { hmWanMbus75 34 }

hmWanMbus75Value0E		OBJECT-TYPE
			SYNTAX	INTEGER
			MAX-ACCESS	read-only
			STATUS	current
			::= { hmWanMbus75 35 }

hmWanMbus75VIF0F		OBJECT-TYPE
			SYNTAX	INTEGER
			MAX-ACCESS	read-only
			STATUS	current
			::= { hmWanMbus75 36 }

hmWanMbus75Value0F		OBJECT-TYPE
			SYNTAX	INTEGER
			MAX-ACCESS	read-only
			STATUS	current
			::= { hmWanMbus75 37 }

hmWanMbus75VIF10		OBJECT-TYPE
			SYNTAX	INTEGER
			MAX-ACCESS	read-only
			STATUS	current
			::= { hmWanMbus75 38 }

hmWanMbus75Value10		OBJECT-TYPE
			SYNTAX	INTEGER
			MAX-ACCESS	read-only
			STATUS	current
			::= { hmWanMbus75 39 }

hmWanMbus75VIF11		OBJECT-TYPE
			SYNTAX	INTEGER
			MAX-ACCESS	read-only
			STATUS	current
			::= { hmWanMbus75 40 }

hmWanMbus75Value11		OBJECT-TYPE
			SYNTAX	INTEGER
			MAX-ACCESS	read-only
			STATUS	current
			::= { hmWanMbus75 41 }

hmWanMbus75VIF12		OBJECT-TYPE
			SYNTAX	INTEGER
			MAX-ACCESS	read-only
			STATUS	current
			::= { hmWanMbus75 42 }

hmWanMbus75Value12		OBJECT-TYPE
			SYNTAX	INTEGER
			MAX-ACCESS	read-only
			STATUS	current
			::= { hmWanMbus75 43 }

hmWanMbus75VIF13		OBJECT-TYPE
			SYNTAX	INTEGER
			MAX-ACCESS	read-only
			STATUS	current
			::= { hmWanMbus75 44 }

hmWanMbus75Value13		OBJECT-TYPE
			SYNTAX	INTEGER
			MAX-ACCESS	read-only
			STATUS	current
			::= { hmWanMbus75 45 }

hmWanMbus75VIF14		OBJECT-TYPE
			SYNTAX	INTEGER
			MAX-ACCESS	read-only
			STATUS	current
			::= { hmWanMbus75 46 }

hmWanMbus75Value14		OBJECT-TYPE
			SYNTAX	INTEGER
			MAX-ACCESS	read-only
			STATUS	current
			::= { hmWanMbus75 47 }

hmWanMbus75VIF15		OBJECT-TYPE
			SYNTAX	INTEGER
			MAX-ACCESS	read-only
			STATUS	current
			::= { hmWanMbus75 48 }

hmWanMbus75Value15		OBJECT-TYPE
			SYNTAX	INTEGER
			MAX-ACCESS	read-only
			STATUS	current
			::= { hmWanMbus75 49 }

hmWanMbus75VIF16		OBJECT-TYPE
			SYNTAX	INTEGER
			MAX-ACCESS	read-only
			STATUS	current
			::= { hmWanMbus75 50 }

hmWanMbus75Value16		OBJECT-TYPE
			SYNTAX	INTEGER
			MAX-ACCESS	read-only
			STATUS	current
			::= { hmWanMbus75 51 }

hmWanMbus75VIF17		OBJECT-TYPE
			SYNTAX	INTEGER
			MAX-ACCESS	read-only
			STATUS	current
			::= { hmWanMbus75 52 }

hmWanMbus75Value17		OBJECT-TYPE
			SYNTAX	INTEGER
			MAX-ACCESS	read-only
			STATUS	current
			::= { hmWanMbus75 53 }

hmWanMbus75VIF18		OBJECT-TYPE
			SYNTAX	INTEGER
			MAX-ACCESS	read-only
			STATUS	current
			::= { hmWanMbus75 54 }

hmWanMbus75Value18		OBJECT-TYPE
			SYNTAX	INTEGER
			MAX-ACCESS	read-only
			STATUS	current
			::= { hmWanMbus75 55 }

hmWanMbus75VIF19		OBJECT-TYPE
			SYNTAX	INTEGER
			MAX-ACCESS	read-only
			STATUS	current
			::= { hmWanMbus75 56 }

hmWanMbus75Value19		OBJECT-TYPE
			SYNTAX	INTEGER
			MAX-ACCESS	read-only
			STATUS	current
			::= { hmWanMbus75 57 }

hmWanMbus75VIF1A		OBJECT-TYPE
			SYNTAX	INTEGER
			MAX-ACCESS	read-only
			STATUS	current
			::= { hmWanMbus75 58 }

hmWanMbus75Value1A		OBJECT-TYPE
			SYNTAX	INTEGER
			MAX-ACCESS	read-only
			STATUS	current
			::= { hmWanMbus75 59 }

hmWanMbus75VIF1B		OBJECT-TYPE
			SYNTAX	INTEGER
			MAX-ACCESS	read-only
			STATUS	current
			::= { hmWanMbus75 60 }

hmWanMbus75Value1B		OBJECT-TYPE
			SYNTAX	INTEGER
			MAX-ACCESS	read-only
			STATUS	current
			::= { hmWanMbus75 61 }

hmWanMbus75VIF1C		OBJECT-TYPE
			SYNTAX	INTEGER
			MAX-ACCESS	read-only
			STATUS	current
			::= { hmWanMbus75 62 }

hmWanMbus75Value1C		OBJECT-TYPE
			SYNTAX	INTEGER
			MAX-ACCESS	read-only
			STATUS	current
			::= { hmWanMbus75 63 }

hmWanMbus75VIF1D		OBJECT-TYPE
			SYNTAX	INTEGER
			MAX-ACCESS	read-only
			STATUS	current
			::= { hmWanMbus75 64 }

hmWanMbus75Value1D		OBJECT-TYPE
			SYNTAX	INTEGER
			MAX-ACCESS	read-only
			STATUS	current
			::= { hmWanMbus75 65 }

hmWanMbus75VIF1E		OBJECT-TYPE
			SYNTAX	INTEGER
			MAX-ACCESS	read-only
			STATUS	current
			::= { hmWanMbus75 66 }

hmWanMbus75Value1E		OBJECT-TYPE
			SYNTAX	INTEGER
			MAX-ACCESS	read-only
			STATUS	current
			::= { hmWanMbus75 67 }

hmWanMbus75VIF1F		OBJECT-TYPE
			SYNTAX	INTEGER
			MAX-ACCESS	read-only
			STATUS	current
			::= { hmWanMbus75 68 }

hmWanMbus75Value1F		OBJECT-TYPE
			SYNTAX	INTEGER
			MAX-ACCESS	read-only
			STATUS	current
			::= { hmWanMbus75 69 }

hmWanMbus75VIF20		OBJECT-TYPE
			SYNTAX	INTEGER
			MAX-ACCESS	read-only
			STATUS	current
			::= { hmWanMbus75 70 }

hmWanMbus75Value20		OBJECT-TYPE
			SYNTAX	INTEGER
			MAX-ACCESS	read-only
			STATUS	current
			::= { hmWanMbus75 71 }

hmWanMbus75VIF21		OBJECT-TYPE
			SYNTAX	INTEGER
			MAX-ACCESS	read-only
			STATUS	current
			::= { hmWanMbus75 72 }

hmWanMbus75Value21		OBJECT-TYPE
			SYNTAX	INTEGER
			MAX-ACCESS	read-only
			STATUS	current
			::= { hmWanMbus75 73 }

hmWanMbus75VIF22		OBJECT-TYPE
			SYNTAX	INTEGER
			MAX-ACCESS	read-only
			STATUS	current
			::= { hmWanMbus75 74 }

hmWanMbus75Value22		OBJECT-TYPE
			SYNTAX	INTEGER
			MAX-ACCESS	read-only
			STATUS	current
			::= { hmWanMbus75 75 }

hmWanMbus75VIF23		OBJECT-TYPE
			SYNTAX	INTEGER
			MAX-ACCESS	read-only
			STATUS	current
			::= { hmWanMbus75 76 }

hmWanMbus75Value23		OBJECT-TYPE
			SYNTAX	INTEGER
			MAX-ACCESS	read-only
			STATUS	current
			::= { hmWanMbus75 77 }

hmWanMbus75VIF24		OBJECT-TYPE
			SYNTAX	INTEGER
			MAX-ACCESS	read-only
			STATUS	current
			::= { hmWanMbus75 78 }

hmWanMbus75Value24		OBJECT-TYPE
			SYNTAX	INTEGER
			MAX-ACCESS	read-only
			STATUS	current
			::= { hmWanMbus75 79 }

hmWanMbus75VIF25		OBJECT-TYPE
			SYNTAX	INTEGER
			MAX-ACCESS	read-only
			STATUS	current
			::= { hmWanMbus75 80 }

hmWanMbus75Value25		OBJECT-TYPE
			SYNTAX	INTEGER
			MAX-ACCESS	read-only
			STATUS	current
			::= { hmWanMbus75 81 }

hmWanMbus75VIF26		OBJECT-TYPE
			SYNTAX	INTEGER
			MAX-ACCESS	read-only
			STATUS	current
			::= { hmWanMbus75 82 }

hmWanMbus75Value26		OBJECT-TYPE
			SYNTAX	INTEGER
			MAX-ACCESS	read-only
			STATUS	current
			::= { hmWanMbus75 83 }

hmWanMbus75VIF27		OBJECT-TYPE
			SYNTAX	INTEGER
			MAX-ACCESS	read-only
			STATUS	current
			::= { hmWanMbus75 84 }

hmWanMbus75Value27		OBJECT-TYPE
			SYNTAX	INTEGER
			MAX-ACCESS	read-only
			STATUS	current
			::= { hmWanMbus75 85 }

hmWanMbus75VIF28		OBJECT-TYPE
			SYNTAX	INTEGER
			MAX-ACCESS	read-only
			STATUS	current
			::= { hmWanMbus75 86 }

hmWanMbus75Value28		OBJECT-TYPE
			SYNTAX	INTEGER
			MAX-ACCESS	read-only
			STATUS	current
			::= { hmWanMbus75 87 }

hmWanMbus75VIF29		OBJECT-TYPE
			SYNTAX	INTEGER
			MAX-ACCESS	read-only
			STATUS	current
			::= { hmWanMbus75 88 }

hmWanMbus75Value29		OBJECT-TYPE
			SYNTAX	INTEGER
			MAX-ACCESS	read-only
			STATUS	current
			::= { hmWanMbus75 89 }

hmWanMbus75VIF2A		OBJECT-TYPE
			SYNTAX	INTEGER
			MAX-ACCESS	read-only
			STATUS	current
			::= { hmWanMbus75 90 }

hmWanMbus75Value2A		OBJECT-TYPE
			SYNTAX	INTEGER
			MAX-ACCESS	read-only
			STATUS	current
			::= { hmWanMbus75 91 }

hmWanMbus75VIF2B		OBJECT-TYPE
			SYNTAX	INTEGER
			MAX-ACCESS	read-only
			STATUS	current
			::= { hmWanMbus75 92 }

hmWanMbus75Value2B		OBJECT-TYPE
			SYNTAX	INTEGER
			MAX-ACCESS	read-only
			STATUS	current
			::= { hmWanMbus75 93 }

hmWanMbus75VIF2C		OBJECT-TYPE
			SYNTAX	INTEGER
			MAX-ACCESS	read-only
			STATUS	current
			::= { hmWanMbus75 94 }

hmWanMbus75Value2C		OBJECT-TYPE
			SYNTAX	INTEGER
			MAX-ACCESS	read-only
			STATUS	current
			::= { hmWanMbus75 95 }

hmWanMbus75VIF2D		OBJECT-TYPE
			SYNTAX	INTEGER
			MAX-ACCESS	read-only
			STATUS	current
			::= { hmWanMbus75 96 }

hmWanMbus75Value2D		OBJECT-TYPE
			SYNTAX	INTEGER
			MAX-ACCESS	read-only
			STATUS	current
			::= { hmWanMbus75 97 }

hmWanMbus75VIF2E		OBJECT-TYPE
			SYNTAX	INTEGER
			MAX-ACCESS	read-only
			STATUS	current
			::= { hmWanMbus75 98 }

hmWanMbus75Value2E		OBJECT-TYPE
			SYNTAX	INTEGER
			MAX-ACCESS	read-only
			STATUS	current
			::= { hmWanMbus75 99 }

hmWanMbus75VIF2F		OBJECT-TYPE
			SYNTAX	INTEGER
			MAX-ACCESS	read-only
			STATUS	current
			::= { hmWanMbus75 100 }

hmWanMbus75Value2F		OBJECT-TYPE
			SYNTAX	INTEGER
			MAX-ACCESS	read-only
			STATUS	current
			::= { hmWanMbus75 101 }

hmWanMbus76			OBJECT IDENTIFIER ::= { hmWanMbus 118 }

hmWanMbus76IdNumber		OBJECT-TYPE
			SYNTAX	Gauge32
			MAX-ACCESS	read-only
			STATUS	current
			::= { hmWanMbus76 1 }

hmWanMbus76Manufacturer	OBJECT-TYPE
			SYNTAX	Gauge32
			MAX-ACCESS	read-only
			STATUS	current
			::= { hmWanMbus76 2 }

hmWanMbus76Version		OBJECT-TYPE
			SYNTAX	Gauge32
			MAX-ACCESS	read-only
			STATUS	current
			::= { hmWanMbus76 3 }

hmWanMbus76Medium		OBJECT-TYPE
			SYNTAX	Gauge32
			MAX-ACCESS	read-only
			STATUS	current
			::= { hmWanMbus76 4 }

hmWanMbus76Status		OBJECT-TYPE
			SYNTAX	Gauge32
			MAX-ACCESS	read-only
			STATUS	current
			::= { hmWanMbus76 5 }

hmWanMbus76VIF00		OBJECT-TYPE
			SYNTAX	INTEGER
			MAX-ACCESS	read-only
			STATUS	current
			::= { hmWanMbus76 6 }

hmWanMbus76Value00		OBJECT-TYPE
			SYNTAX	INTEGER
			MAX-ACCESS	read-only
			STATUS	current
			::= { hmWanMbus76 7 }

hmWanMbus76VIF01		OBJECT-TYPE
			SYNTAX	INTEGER
			MAX-ACCESS	read-only
			STATUS	current
			::= { hmWanMbus76 8 }

hmWanMbus76Value01		OBJECT-TYPE
			SYNTAX	INTEGER
			MAX-ACCESS	read-only
			STATUS	current
			::= { hmWanMbus76 9 }

hmWanMbus76VIF02		OBJECT-TYPE
			SYNTAX	INTEGER
			MAX-ACCESS	read-only
			STATUS	current
			::= { hmWanMbus76 10 }

hmWanMbus76Value02		OBJECT-TYPE
			SYNTAX	INTEGER
			MAX-ACCESS	read-only
			STATUS	current
			::= { hmWanMbus76 11 }

hmWanMbus76VIF03		OBJECT-TYPE
			SYNTAX	INTEGER
			MAX-ACCESS	read-only
			STATUS	current
			::= { hmWanMbus76 12 }

hmWanMbus76Value03		OBJECT-TYPE
			SYNTAX	INTEGER
			MAX-ACCESS	read-only
			STATUS	current
			::= { hmWanMbus76 13 }

hmWanMbus76VIF04		OBJECT-TYPE
			SYNTAX	INTEGER
			MAX-ACCESS	read-only
			STATUS	current
			::= { hmWanMbus76 14 }

hmWanMbus76Value04		OBJECT-TYPE
			SYNTAX	INTEGER
			MAX-ACCESS	read-only
			STATUS	current
			::= { hmWanMbus76 15 }

hmWanMbus76VIF05		OBJECT-TYPE
			SYNTAX	INTEGER
			MAX-ACCESS	read-only
			STATUS	current
			::= { hmWanMbus76 16 }

hmWanMbus76Value05		OBJECT-TYPE
			SYNTAX	INTEGER
			MAX-ACCESS	read-only
			STATUS	current
			::= { hmWanMbus76 17 }

hmWanMbus76VIF06		OBJECT-TYPE
			SYNTAX	INTEGER
			MAX-ACCESS	read-only
			STATUS	current
			::= { hmWanMbus76 18 }

hmWanMbus76Value06		OBJECT-TYPE
			SYNTAX	INTEGER
			MAX-ACCESS	read-only
			STATUS	current
			::= { hmWanMbus76 19 }

hmWanMbus76VIF07		OBJECT-TYPE
			SYNTAX	INTEGER
			MAX-ACCESS	read-only
			STATUS	current
			::= { hmWanMbus76 20 }

hmWanMbus76Value07		OBJECT-TYPE
			SYNTAX	INTEGER
			MAX-ACCESS	read-only
			STATUS	current
			::= { hmWanMbus76 21 }

hmWanMbus76VIF08		OBJECT-TYPE
			SYNTAX	INTEGER
			MAX-ACCESS	read-only
			STATUS	current
			::= { hmWanMbus76 22 }

hmWanMbus76Value08		OBJECT-TYPE
			SYNTAX	INTEGER
			MAX-ACCESS	read-only
			STATUS	current
			::= { hmWanMbus76 23 }

hmWanMbus76VIF09		OBJECT-TYPE
			SYNTAX	INTEGER
			MAX-ACCESS	read-only
			STATUS	current
			::= { hmWanMbus76 24 }

hmWanMbus76Value09		OBJECT-TYPE
			SYNTAX	INTEGER
			MAX-ACCESS	read-only
			STATUS	current
			::= { hmWanMbus76 25 }

hmWanMbus76VIF0A		OBJECT-TYPE
			SYNTAX	INTEGER
			MAX-ACCESS	read-only
			STATUS	current
			::= { hmWanMbus76 26 }

hmWanMbus76Value0A		OBJECT-TYPE
			SYNTAX	INTEGER
			MAX-ACCESS	read-only
			STATUS	current
			::= { hmWanMbus76 27 }

hmWanMbus76VIF0B		OBJECT-TYPE
			SYNTAX	INTEGER
			MAX-ACCESS	read-only
			STATUS	current
			::= { hmWanMbus76 28 }

hmWanMbus76Value0B		OBJECT-TYPE
			SYNTAX	INTEGER
			MAX-ACCESS	read-only
			STATUS	current
			::= { hmWanMbus76 29 }

hmWanMbus76VIF0C		OBJECT-TYPE
			SYNTAX	INTEGER
			MAX-ACCESS	read-only
			STATUS	current
			::= { hmWanMbus76 30 }

hmWanMbus76Value0C		OBJECT-TYPE
			SYNTAX	INTEGER
			MAX-ACCESS	read-only
			STATUS	current
			::= { hmWanMbus76 31 }

hmWanMbus76VIF0D		OBJECT-TYPE
			SYNTAX	INTEGER
			MAX-ACCESS	read-only
			STATUS	current
			::= { hmWanMbus76 32 }

hmWanMbus76Value0D		OBJECT-TYPE
			SYNTAX	INTEGER
			MAX-ACCESS	read-only
			STATUS	current
			::= { hmWanMbus76 33 }

hmWanMbus76VIF0E		OBJECT-TYPE
			SYNTAX	INTEGER
			MAX-ACCESS	read-only
			STATUS	current
			::= { hmWanMbus76 34 }

hmWanMbus76Value0E		OBJECT-TYPE
			SYNTAX	INTEGER
			MAX-ACCESS	read-only
			STATUS	current
			::= { hmWanMbus76 35 }

hmWanMbus76VIF0F		OBJECT-TYPE
			SYNTAX	INTEGER
			MAX-ACCESS	read-only
			STATUS	current
			::= { hmWanMbus76 36 }

hmWanMbus76Value0F		OBJECT-TYPE
			SYNTAX	INTEGER
			MAX-ACCESS	read-only
			STATUS	current
			::= { hmWanMbus76 37 }

hmWanMbus76VIF10		OBJECT-TYPE
			SYNTAX	INTEGER
			MAX-ACCESS	read-only
			STATUS	current
			::= { hmWanMbus76 38 }

hmWanMbus76Value10		OBJECT-TYPE
			SYNTAX	INTEGER
			MAX-ACCESS	read-only
			STATUS	current
			::= { hmWanMbus76 39 }

hmWanMbus76VIF11		OBJECT-TYPE
			SYNTAX	INTEGER
			MAX-ACCESS	read-only
			STATUS	current
			::= { hmWanMbus76 40 }

hmWanMbus76Value11		OBJECT-TYPE
			SYNTAX	INTEGER
			MAX-ACCESS	read-only
			STATUS	current
			::= { hmWanMbus76 41 }

hmWanMbus76VIF12		OBJECT-TYPE
			SYNTAX	INTEGER
			MAX-ACCESS	read-only
			STATUS	current
			::= { hmWanMbus76 42 }

hmWanMbus76Value12		OBJECT-TYPE
			SYNTAX	INTEGER
			MAX-ACCESS	read-only
			STATUS	current
			::= { hmWanMbus76 43 }

hmWanMbus76VIF13		OBJECT-TYPE
			SYNTAX	INTEGER
			MAX-ACCESS	read-only
			STATUS	current
			::= { hmWanMbus76 44 }

hmWanMbus76Value13		OBJECT-TYPE
			SYNTAX	INTEGER
			MAX-ACCESS	read-only
			STATUS	current
			::= { hmWanMbus76 45 }

hmWanMbus76VIF14		OBJECT-TYPE
			SYNTAX	INTEGER
			MAX-ACCESS	read-only
			STATUS	current
			::= { hmWanMbus76 46 }

hmWanMbus76Value14		OBJECT-TYPE
			SYNTAX	INTEGER
			MAX-ACCESS	read-only
			STATUS	current
			::= { hmWanMbus76 47 }

hmWanMbus76VIF15		OBJECT-TYPE
			SYNTAX	INTEGER
			MAX-ACCESS	read-only
			STATUS	current
			::= { hmWanMbus76 48 }

hmWanMbus76Value15		OBJECT-TYPE
			SYNTAX	INTEGER
			MAX-ACCESS	read-only
			STATUS	current
			::= { hmWanMbus76 49 }

hmWanMbus76VIF16		OBJECT-TYPE
			SYNTAX	INTEGER
			MAX-ACCESS	read-only
			STATUS	current
			::= { hmWanMbus76 50 }

hmWanMbus76Value16		OBJECT-TYPE
			SYNTAX	INTEGER
			MAX-ACCESS	read-only
			STATUS	current
			::= { hmWanMbus76 51 }

hmWanMbus76VIF17		OBJECT-TYPE
			SYNTAX	INTEGER
			MAX-ACCESS	read-only
			STATUS	current
			::= { hmWanMbus76 52 }

hmWanMbus76Value17		OBJECT-TYPE
			SYNTAX	INTEGER
			MAX-ACCESS	read-only
			STATUS	current
			::= { hmWanMbus76 53 }

hmWanMbus76VIF18		OBJECT-TYPE
			SYNTAX	INTEGER
			MAX-ACCESS	read-only
			STATUS	current
			::= { hmWanMbus76 54 }

hmWanMbus76Value18		OBJECT-TYPE
			SYNTAX	INTEGER
			MAX-ACCESS	read-only
			STATUS	current
			::= { hmWanMbus76 55 }

hmWanMbus76VIF19		OBJECT-TYPE
			SYNTAX	INTEGER
			MAX-ACCESS	read-only
			STATUS	current
			::= { hmWanMbus76 56 }

hmWanMbus76Value19		OBJECT-TYPE
			SYNTAX	INTEGER
			MAX-ACCESS	read-only
			STATUS	current
			::= { hmWanMbus76 57 }

hmWanMbus76VIF1A		OBJECT-TYPE
			SYNTAX	INTEGER
			MAX-ACCESS	read-only
			STATUS	current
			::= { hmWanMbus76 58 }

hmWanMbus76Value1A		OBJECT-TYPE
			SYNTAX	INTEGER
			MAX-ACCESS	read-only
			STATUS	current
			::= { hmWanMbus76 59 }

hmWanMbus76VIF1B		OBJECT-TYPE
			SYNTAX	INTEGER
			MAX-ACCESS	read-only
			STATUS	current
			::= { hmWanMbus76 60 }

hmWanMbus76Value1B		OBJECT-TYPE
			SYNTAX	INTEGER
			MAX-ACCESS	read-only
			STATUS	current
			::= { hmWanMbus76 61 }

hmWanMbus76VIF1C		OBJECT-TYPE
			SYNTAX	INTEGER
			MAX-ACCESS	read-only
			STATUS	current
			::= { hmWanMbus76 62 }

hmWanMbus76Value1C		OBJECT-TYPE
			SYNTAX	INTEGER
			MAX-ACCESS	read-only
			STATUS	current
			::= { hmWanMbus76 63 }

hmWanMbus76VIF1D		OBJECT-TYPE
			SYNTAX	INTEGER
			MAX-ACCESS	read-only
			STATUS	current
			::= { hmWanMbus76 64 }

hmWanMbus76Value1D		OBJECT-TYPE
			SYNTAX	INTEGER
			MAX-ACCESS	read-only
			STATUS	current
			::= { hmWanMbus76 65 }

hmWanMbus76VIF1E		OBJECT-TYPE
			SYNTAX	INTEGER
			MAX-ACCESS	read-only
			STATUS	current
			::= { hmWanMbus76 66 }

hmWanMbus76Value1E		OBJECT-TYPE
			SYNTAX	INTEGER
			MAX-ACCESS	read-only
			STATUS	current
			::= { hmWanMbus76 67 }

hmWanMbus76VIF1F		OBJECT-TYPE
			SYNTAX	INTEGER
			MAX-ACCESS	read-only
			STATUS	current
			::= { hmWanMbus76 68 }

hmWanMbus76Value1F		OBJECT-TYPE
			SYNTAX	INTEGER
			MAX-ACCESS	read-only
			STATUS	current
			::= { hmWanMbus76 69 }

hmWanMbus76VIF20		OBJECT-TYPE
			SYNTAX	INTEGER
			MAX-ACCESS	read-only
			STATUS	current
			::= { hmWanMbus76 70 }

hmWanMbus76Value20		OBJECT-TYPE
			SYNTAX	INTEGER
			MAX-ACCESS	read-only
			STATUS	current
			::= { hmWanMbus76 71 }

hmWanMbus76VIF21		OBJECT-TYPE
			SYNTAX	INTEGER
			MAX-ACCESS	read-only
			STATUS	current
			::= { hmWanMbus76 72 }

hmWanMbus76Value21		OBJECT-TYPE
			SYNTAX	INTEGER
			MAX-ACCESS	read-only
			STATUS	current
			::= { hmWanMbus76 73 }

hmWanMbus76VIF22		OBJECT-TYPE
			SYNTAX	INTEGER
			MAX-ACCESS	read-only
			STATUS	current
			::= { hmWanMbus76 74 }

hmWanMbus76Value22		OBJECT-TYPE
			SYNTAX	INTEGER
			MAX-ACCESS	read-only
			STATUS	current
			::= { hmWanMbus76 75 }

hmWanMbus76VIF23		OBJECT-TYPE
			SYNTAX	INTEGER
			MAX-ACCESS	read-only
			STATUS	current
			::= { hmWanMbus76 76 }

hmWanMbus76Value23		OBJECT-TYPE
			SYNTAX	INTEGER
			MAX-ACCESS	read-only
			STATUS	current
			::= { hmWanMbus76 77 }

hmWanMbus76VIF24		OBJECT-TYPE
			SYNTAX	INTEGER
			MAX-ACCESS	read-only
			STATUS	current
			::= { hmWanMbus76 78 }

hmWanMbus76Value24		OBJECT-TYPE
			SYNTAX	INTEGER
			MAX-ACCESS	read-only
			STATUS	current
			::= { hmWanMbus76 79 }

hmWanMbus76VIF25		OBJECT-TYPE
			SYNTAX	INTEGER
			MAX-ACCESS	read-only
			STATUS	current
			::= { hmWanMbus76 80 }

hmWanMbus76Value25		OBJECT-TYPE
			SYNTAX	INTEGER
			MAX-ACCESS	read-only
			STATUS	current
			::= { hmWanMbus76 81 }

hmWanMbus76VIF26		OBJECT-TYPE
			SYNTAX	INTEGER
			MAX-ACCESS	read-only
			STATUS	current
			::= { hmWanMbus76 82 }

hmWanMbus76Value26		OBJECT-TYPE
			SYNTAX	INTEGER
			MAX-ACCESS	read-only
			STATUS	current
			::= { hmWanMbus76 83 }

hmWanMbus76VIF27		OBJECT-TYPE
			SYNTAX	INTEGER
			MAX-ACCESS	read-only
			STATUS	current
			::= { hmWanMbus76 84 }

hmWanMbus76Value27		OBJECT-TYPE
			SYNTAX	INTEGER
			MAX-ACCESS	read-only
			STATUS	current
			::= { hmWanMbus76 85 }

hmWanMbus76VIF28		OBJECT-TYPE
			SYNTAX	INTEGER
			MAX-ACCESS	read-only
			STATUS	current
			::= { hmWanMbus76 86 }

hmWanMbus76Value28		OBJECT-TYPE
			SYNTAX	INTEGER
			MAX-ACCESS	read-only
			STATUS	current
			::= { hmWanMbus76 87 }

hmWanMbus76VIF29		OBJECT-TYPE
			SYNTAX	INTEGER
			MAX-ACCESS	read-only
			STATUS	current
			::= { hmWanMbus76 88 }

hmWanMbus76Value29		OBJECT-TYPE
			SYNTAX	INTEGER
			MAX-ACCESS	read-only
			STATUS	current
			::= { hmWanMbus76 89 }

hmWanMbus76VIF2A		OBJECT-TYPE
			SYNTAX	INTEGER
			MAX-ACCESS	read-only
			STATUS	current
			::= { hmWanMbus76 90 }

hmWanMbus76Value2A		OBJECT-TYPE
			SYNTAX	INTEGER
			MAX-ACCESS	read-only
			STATUS	current
			::= { hmWanMbus76 91 }

hmWanMbus76VIF2B		OBJECT-TYPE
			SYNTAX	INTEGER
			MAX-ACCESS	read-only
			STATUS	current
			::= { hmWanMbus76 92 }

hmWanMbus76Value2B		OBJECT-TYPE
			SYNTAX	INTEGER
			MAX-ACCESS	read-only
			STATUS	current
			::= { hmWanMbus76 93 }

hmWanMbus76VIF2C		OBJECT-TYPE
			SYNTAX	INTEGER
			MAX-ACCESS	read-only
			STATUS	current
			::= { hmWanMbus76 94 }

hmWanMbus76Value2C		OBJECT-TYPE
			SYNTAX	INTEGER
			MAX-ACCESS	read-only
			STATUS	current
			::= { hmWanMbus76 95 }

hmWanMbus76VIF2D		OBJECT-TYPE
			SYNTAX	INTEGER
			MAX-ACCESS	read-only
			STATUS	current
			::= { hmWanMbus76 96 }

hmWanMbus76Value2D		OBJECT-TYPE
			SYNTAX	INTEGER
			MAX-ACCESS	read-only
			STATUS	current
			::= { hmWanMbus76 97 }

hmWanMbus76VIF2E		OBJECT-TYPE
			SYNTAX	INTEGER
			MAX-ACCESS	read-only
			STATUS	current
			::= { hmWanMbus76 98 }

hmWanMbus76Value2E		OBJECT-TYPE
			SYNTAX	INTEGER
			MAX-ACCESS	read-only
			STATUS	current
			::= { hmWanMbus76 99 }

hmWanMbus76VIF2F		OBJECT-TYPE
			SYNTAX	INTEGER
			MAX-ACCESS	read-only
			STATUS	current
			::= { hmWanMbus76 100 }

hmWanMbus76Value2F		OBJECT-TYPE
			SYNTAX	INTEGER
			MAX-ACCESS	read-only
			STATUS	current
			::= { hmWanMbus76 101 }

hmWanMbus77			OBJECT IDENTIFIER ::= { hmWanMbus 119 }

hmWanMbus77IdNumber		OBJECT-TYPE
			SYNTAX	Gauge32
			MAX-ACCESS	read-only
			STATUS	current
			::= { hmWanMbus77 1 }

hmWanMbus77Manufacturer	OBJECT-TYPE
			SYNTAX	Gauge32
			MAX-ACCESS	read-only
			STATUS	current
			::= { hmWanMbus77 2 }

hmWanMbus77Version		OBJECT-TYPE
			SYNTAX	Gauge32
			MAX-ACCESS	read-only
			STATUS	current
			::= { hmWanMbus77 3 }

hmWanMbus77Medium		OBJECT-TYPE
			SYNTAX	Gauge32
			MAX-ACCESS	read-only
			STATUS	current
			::= { hmWanMbus77 4 }

hmWanMbus77Status		OBJECT-TYPE
			SYNTAX	Gauge32
			MAX-ACCESS	read-only
			STATUS	current
			::= { hmWanMbus77 5 }

hmWanMbus77VIF00		OBJECT-TYPE
			SYNTAX	INTEGER
			MAX-ACCESS	read-only
			STATUS	current
			::= { hmWanMbus77 6 }

hmWanMbus77Value00		OBJECT-TYPE
			SYNTAX	INTEGER
			MAX-ACCESS	read-only
			STATUS	current
			::= { hmWanMbus77 7 }

hmWanMbus77VIF01		OBJECT-TYPE
			SYNTAX	INTEGER
			MAX-ACCESS	read-only
			STATUS	current
			::= { hmWanMbus77 8 }

hmWanMbus77Value01		OBJECT-TYPE
			SYNTAX	INTEGER
			MAX-ACCESS	read-only
			STATUS	current
			::= { hmWanMbus77 9 }

hmWanMbus77VIF02		OBJECT-TYPE
			SYNTAX	INTEGER
			MAX-ACCESS	read-only
			STATUS	current
			::= { hmWanMbus77 10 }

hmWanMbus77Value02		OBJECT-TYPE
			SYNTAX	INTEGER
			MAX-ACCESS	read-only
			STATUS	current
			::= { hmWanMbus77 11 }

hmWanMbus77VIF03		OBJECT-TYPE
			SYNTAX	INTEGER
			MAX-ACCESS	read-only
			STATUS	current
			::= { hmWanMbus77 12 }

hmWanMbus77Value03		OBJECT-TYPE
			SYNTAX	INTEGER
			MAX-ACCESS	read-only
			STATUS	current
			::= { hmWanMbus77 13 }

hmWanMbus77VIF04		OBJECT-TYPE
			SYNTAX	INTEGER
			MAX-ACCESS	read-only
			STATUS	current
			::= { hmWanMbus77 14 }

hmWanMbus77Value04		OBJECT-TYPE
			SYNTAX	INTEGER
			MAX-ACCESS	read-only
			STATUS	current
			::= { hmWanMbus77 15 }

hmWanMbus77VIF05		OBJECT-TYPE
			SYNTAX	INTEGER
			MAX-ACCESS	read-only
			STATUS	current
			::= { hmWanMbus77 16 }

hmWanMbus77Value05		OBJECT-TYPE
			SYNTAX	INTEGER
			MAX-ACCESS	read-only
			STATUS	current
			::= { hmWanMbus77 17 }

hmWanMbus77VIF06		OBJECT-TYPE
			SYNTAX	INTEGER
			MAX-ACCESS	read-only
			STATUS	current
			::= { hmWanMbus77 18 }

hmWanMbus77Value06		OBJECT-TYPE
			SYNTAX	INTEGER
			MAX-ACCESS	read-only
			STATUS	current
			::= { hmWanMbus77 19 }

hmWanMbus77VIF07		OBJECT-TYPE
			SYNTAX	INTEGER
			MAX-ACCESS	read-only
			STATUS	current
			::= { hmWanMbus77 20 }

hmWanMbus77Value07		OBJECT-TYPE
			SYNTAX	INTEGER
			MAX-ACCESS	read-only
			STATUS	current
			::= { hmWanMbus77 21 }

hmWanMbus77VIF08		OBJECT-TYPE
			SYNTAX	INTEGER
			MAX-ACCESS	read-only
			STATUS	current
			::= { hmWanMbus77 22 }

hmWanMbus77Value08		OBJECT-TYPE
			SYNTAX	INTEGER
			MAX-ACCESS	read-only
			STATUS	current
			::= { hmWanMbus77 23 }

hmWanMbus77VIF09		OBJECT-TYPE
			SYNTAX	INTEGER
			MAX-ACCESS	read-only
			STATUS	current
			::= { hmWanMbus77 24 }

hmWanMbus77Value09		OBJECT-TYPE
			SYNTAX	INTEGER
			MAX-ACCESS	read-only
			STATUS	current
			::= { hmWanMbus77 25 }

hmWanMbus77VIF0A		OBJECT-TYPE
			SYNTAX	INTEGER
			MAX-ACCESS	read-only
			STATUS	current
			::= { hmWanMbus77 26 }

hmWanMbus77Value0A		OBJECT-TYPE
			SYNTAX	INTEGER
			MAX-ACCESS	read-only
			STATUS	current
			::= { hmWanMbus77 27 }

hmWanMbus77VIF0B		OBJECT-TYPE
			SYNTAX	INTEGER
			MAX-ACCESS	read-only
			STATUS	current
			::= { hmWanMbus77 28 }

hmWanMbus77Value0B		OBJECT-TYPE
			SYNTAX	INTEGER
			MAX-ACCESS	read-only
			STATUS	current
			::= { hmWanMbus77 29 }

hmWanMbus77VIF0C		OBJECT-TYPE
			SYNTAX	INTEGER
			MAX-ACCESS	read-only
			STATUS	current
			::= { hmWanMbus77 30 }

hmWanMbus77Value0C		OBJECT-TYPE
			SYNTAX	INTEGER
			MAX-ACCESS	read-only
			STATUS	current
			::= { hmWanMbus77 31 }

hmWanMbus77VIF0D		OBJECT-TYPE
			SYNTAX	INTEGER
			MAX-ACCESS	read-only
			STATUS	current
			::= { hmWanMbus77 32 }

hmWanMbus77Value0D		OBJECT-TYPE
			SYNTAX	INTEGER
			MAX-ACCESS	read-only
			STATUS	current
			::= { hmWanMbus77 33 }

hmWanMbus77VIF0E		OBJECT-TYPE
			SYNTAX	INTEGER
			MAX-ACCESS	read-only
			STATUS	current
			::= { hmWanMbus77 34 }

hmWanMbus77Value0E		OBJECT-TYPE
			SYNTAX	INTEGER
			MAX-ACCESS	read-only
			STATUS	current
			::= { hmWanMbus77 35 }

hmWanMbus77VIF0F		OBJECT-TYPE
			SYNTAX	INTEGER
			MAX-ACCESS	read-only
			STATUS	current
			::= { hmWanMbus77 36 }

hmWanMbus77Value0F		OBJECT-TYPE
			SYNTAX	INTEGER
			MAX-ACCESS	read-only
			STATUS	current
			::= { hmWanMbus77 37 }

hmWanMbus77VIF10		OBJECT-TYPE
			SYNTAX	INTEGER
			MAX-ACCESS	read-only
			STATUS	current
			::= { hmWanMbus77 38 }

hmWanMbus77Value10		OBJECT-TYPE
			SYNTAX	INTEGER
			MAX-ACCESS	read-only
			STATUS	current
			::= { hmWanMbus77 39 }

hmWanMbus77VIF11		OBJECT-TYPE
			SYNTAX	INTEGER
			MAX-ACCESS	read-only
			STATUS	current
			::= { hmWanMbus77 40 }

hmWanMbus77Value11		OBJECT-TYPE
			SYNTAX	INTEGER
			MAX-ACCESS	read-only
			STATUS	current
			::= { hmWanMbus77 41 }

hmWanMbus77VIF12		OBJECT-TYPE
			SYNTAX	INTEGER
			MAX-ACCESS	read-only
			STATUS	current
			::= { hmWanMbus77 42 }

hmWanMbus77Value12		OBJECT-TYPE
			SYNTAX	INTEGER
			MAX-ACCESS	read-only
			STATUS	current
			::= { hmWanMbus77 43 }

hmWanMbus77VIF13		OBJECT-TYPE
			SYNTAX	INTEGER
			MAX-ACCESS	read-only
			STATUS	current
			::= { hmWanMbus77 44 }

hmWanMbus77Value13		OBJECT-TYPE
			SYNTAX	INTEGER
			MAX-ACCESS	read-only
			STATUS	current
			::= { hmWanMbus77 45 }

hmWanMbus77VIF14		OBJECT-TYPE
			SYNTAX	INTEGER
			MAX-ACCESS	read-only
			STATUS	current
			::= { hmWanMbus77 46 }

hmWanMbus77Value14		OBJECT-TYPE
			SYNTAX	INTEGER
			MAX-ACCESS	read-only
			STATUS	current
			::= { hmWanMbus77 47 }

hmWanMbus77VIF15		OBJECT-TYPE
			SYNTAX	INTEGER
			MAX-ACCESS	read-only
			STATUS	current
			::= { hmWanMbus77 48 }

hmWanMbus77Value15		OBJECT-TYPE
			SYNTAX	INTEGER
			MAX-ACCESS	read-only
			STATUS	current
			::= { hmWanMbus77 49 }

hmWanMbus77VIF16		OBJECT-TYPE
			SYNTAX	INTEGER
			MAX-ACCESS	read-only
			STATUS	current
			::= { hmWanMbus77 50 }

hmWanMbus77Value16		OBJECT-TYPE
			SYNTAX	INTEGER
			MAX-ACCESS	read-only
			STATUS	current
			::= { hmWanMbus77 51 }

hmWanMbus77VIF17		OBJECT-TYPE
			SYNTAX	INTEGER
			MAX-ACCESS	read-only
			STATUS	current
			::= { hmWanMbus77 52 }

hmWanMbus77Value17		OBJECT-TYPE
			SYNTAX	INTEGER
			MAX-ACCESS	read-only
			STATUS	current
			::= { hmWanMbus77 53 }

hmWanMbus77VIF18		OBJECT-TYPE
			SYNTAX	INTEGER
			MAX-ACCESS	read-only
			STATUS	current
			::= { hmWanMbus77 54 }

hmWanMbus77Value18		OBJECT-TYPE
			SYNTAX	INTEGER
			MAX-ACCESS	read-only
			STATUS	current
			::= { hmWanMbus77 55 }

hmWanMbus77VIF19		OBJECT-TYPE
			SYNTAX	INTEGER
			MAX-ACCESS	read-only
			STATUS	current
			::= { hmWanMbus77 56 }

hmWanMbus77Value19		OBJECT-TYPE
			SYNTAX	INTEGER
			MAX-ACCESS	read-only
			STATUS	current
			::= { hmWanMbus77 57 }

hmWanMbus77VIF1A		OBJECT-TYPE
			SYNTAX	INTEGER
			MAX-ACCESS	read-only
			STATUS	current
			::= { hmWanMbus77 58 }

hmWanMbus77Value1A		OBJECT-TYPE
			SYNTAX	INTEGER
			MAX-ACCESS	read-only
			STATUS	current
			::= { hmWanMbus77 59 }

hmWanMbus77VIF1B		OBJECT-TYPE
			SYNTAX	INTEGER
			MAX-ACCESS	read-only
			STATUS	current
			::= { hmWanMbus77 60 }

hmWanMbus77Value1B		OBJECT-TYPE
			SYNTAX	INTEGER
			MAX-ACCESS	read-only
			STATUS	current
			::= { hmWanMbus77 61 }

hmWanMbus77VIF1C		OBJECT-TYPE
			SYNTAX	INTEGER
			MAX-ACCESS	read-only
			STATUS	current
			::= { hmWanMbus77 62 }

hmWanMbus77Value1C		OBJECT-TYPE
			SYNTAX	INTEGER
			MAX-ACCESS	read-only
			STATUS	current
			::= { hmWanMbus77 63 }

hmWanMbus77VIF1D		OBJECT-TYPE
			SYNTAX	INTEGER
			MAX-ACCESS	read-only
			STATUS	current
			::= { hmWanMbus77 64 }

hmWanMbus77Value1D		OBJECT-TYPE
			SYNTAX	INTEGER
			MAX-ACCESS	read-only
			STATUS	current
			::= { hmWanMbus77 65 }

hmWanMbus77VIF1E		OBJECT-TYPE
			SYNTAX	INTEGER
			MAX-ACCESS	read-only
			STATUS	current
			::= { hmWanMbus77 66 }

hmWanMbus77Value1E		OBJECT-TYPE
			SYNTAX	INTEGER
			MAX-ACCESS	read-only
			STATUS	current
			::= { hmWanMbus77 67 }

hmWanMbus77VIF1F		OBJECT-TYPE
			SYNTAX	INTEGER
			MAX-ACCESS	read-only
			STATUS	current
			::= { hmWanMbus77 68 }

hmWanMbus77Value1F		OBJECT-TYPE
			SYNTAX	INTEGER
			MAX-ACCESS	read-only
			STATUS	current
			::= { hmWanMbus77 69 }

hmWanMbus77VIF20		OBJECT-TYPE
			SYNTAX	INTEGER
			MAX-ACCESS	read-only
			STATUS	current
			::= { hmWanMbus77 70 }

hmWanMbus77Value20		OBJECT-TYPE
			SYNTAX	INTEGER
			MAX-ACCESS	read-only
			STATUS	current
			::= { hmWanMbus77 71 }

hmWanMbus77VIF21		OBJECT-TYPE
			SYNTAX	INTEGER
			MAX-ACCESS	read-only
			STATUS	current
			::= { hmWanMbus77 72 }

hmWanMbus77Value21		OBJECT-TYPE
			SYNTAX	INTEGER
			MAX-ACCESS	read-only
			STATUS	current
			::= { hmWanMbus77 73 }

hmWanMbus77VIF22		OBJECT-TYPE
			SYNTAX	INTEGER
			MAX-ACCESS	read-only
			STATUS	current
			::= { hmWanMbus77 74 }

hmWanMbus77Value22		OBJECT-TYPE
			SYNTAX	INTEGER
			MAX-ACCESS	read-only
			STATUS	current
			::= { hmWanMbus77 75 }

hmWanMbus77VIF23		OBJECT-TYPE
			SYNTAX	INTEGER
			MAX-ACCESS	read-only
			STATUS	current
			::= { hmWanMbus77 76 }

hmWanMbus77Value23		OBJECT-TYPE
			SYNTAX	INTEGER
			MAX-ACCESS	read-only
			STATUS	current
			::= { hmWanMbus77 77 }

hmWanMbus77VIF24		OBJECT-TYPE
			SYNTAX	INTEGER
			MAX-ACCESS	read-only
			STATUS	current
			::= { hmWanMbus77 78 }

hmWanMbus77Value24		OBJECT-TYPE
			SYNTAX	INTEGER
			MAX-ACCESS	read-only
			STATUS	current
			::= { hmWanMbus77 79 }

hmWanMbus77VIF25		OBJECT-TYPE
			SYNTAX	INTEGER
			MAX-ACCESS	read-only
			STATUS	current
			::= { hmWanMbus77 80 }

hmWanMbus77Value25		OBJECT-TYPE
			SYNTAX	INTEGER
			MAX-ACCESS	read-only
			STATUS	current
			::= { hmWanMbus77 81 }

hmWanMbus77VIF26		OBJECT-TYPE
			SYNTAX	INTEGER
			MAX-ACCESS	read-only
			STATUS	current
			::= { hmWanMbus77 82 }

hmWanMbus77Value26		OBJECT-TYPE
			SYNTAX	INTEGER
			MAX-ACCESS	read-only
			STATUS	current
			::= { hmWanMbus77 83 }

hmWanMbus77VIF27		OBJECT-TYPE
			SYNTAX	INTEGER
			MAX-ACCESS	read-only
			STATUS	current
			::= { hmWanMbus77 84 }

hmWanMbus77Value27		OBJECT-TYPE
			SYNTAX	INTEGER
			MAX-ACCESS	read-only
			STATUS	current
			::= { hmWanMbus77 85 }

hmWanMbus77VIF28		OBJECT-TYPE
			SYNTAX	INTEGER
			MAX-ACCESS	read-only
			STATUS	current
			::= { hmWanMbus77 86 }

hmWanMbus77Value28		OBJECT-TYPE
			SYNTAX	INTEGER
			MAX-ACCESS	read-only
			STATUS	current
			::= { hmWanMbus77 87 }

hmWanMbus77VIF29		OBJECT-TYPE
			SYNTAX	INTEGER
			MAX-ACCESS	read-only
			STATUS	current
			::= { hmWanMbus77 88 }

hmWanMbus77Value29		OBJECT-TYPE
			SYNTAX	INTEGER
			MAX-ACCESS	read-only
			STATUS	current
			::= { hmWanMbus77 89 }

hmWanMbus77VIF2A		OBJECT-TYPE
			SYNTAX	INTEGER
			MAX-ACCESS	read-only
			STATUS	current
			::= { hmWanMbus77 90 }

hmWanMbus77Value2A		OBJECT-TYPE
			SYNTAX	INTEGER
			MAX-ACCESS	read-only
			STATUS	current
			::= { hmWanMbus77 91 }

hmWanMbus77VIF2B		OBJECT-TYPE
			SYNTAX	INTEGER
			MAX-ACCESS	read-only
			STATUS	current
			::= { hmWanMbus77 92 }

hmWanMbus77Value2B		OBJECT-TYPE
			SYNTAX	INTEGER
			MAX-ACCESS	read-only
			STATUS	current
			::= { hmWanMbus77 93 }

hmWanMbus77VIF2C		OBJECT-TYPE
			SYNTAX	INTEGER
			MAX-ACCESS	read-only
			STATUS	current
			::= { hmWanMbus77 94 }

hmWanMbus77Value2C		OBJECT-TYPE
			SYNTAX	INTEGER
			MAX-ACCESS	read-only
			STATUS	current
			::= { hmWanMbus77 95 }

hmWanMbus77VIF2D		OBJECT-TYPE
			SYNTAX	INTEGER
			MAX-ACCESS	read-only
			STATUS	current
			::= { hmWanMbus77 96 }

hmWanMbus77Value2D		OBJECT-TYPE
			SYNTAX	INTEGER
			MAX-ACCESS	read-only
			STATUS	current
			::= { hmWanMbus77 97 }

hmWanMbus77VIF2E		OBJECT-TYPE
			SYNTAX	INTEGER
			MAX-ACCESS	read-only
			STATUS	current
			::= { hmWanMbus77 98 }

hmWanMbus77Value2E		OBJECT-TYPE
			SYNTAX	INTEGER
			MAX-ACCESS	read-only
			STATUS	current
			::= { hmWanMbus77 99 }

hmWanMbus77VIF2F		OBJECT-TYPE
			SYNTAX	INTEGER
			MAX-ACCESS	read-only
			STATUS	current
			::= { hmWanMbus77 100 }

hmWanMbus77Value2F		OBJECT-TYPE
			SYNTAX	INTEGER
			MAX-ACCESS	read-only
			STATUS	current
			::= { hmWanMbus77 101 }

hmWanMbus78			OBJECT IDENTIFIER ::= { hmWanMbus 120 }

hmWanMbus78IdNumber		OBJECT-TYPE
			SYNTAX	Gauge32
			MAX-ACCESS	read-only
			STATUS	current
			::= { hmWanMbus78 1 }

hmWanMbus78Manufacturer	OBJECT-TYPE
			SYNTAX	Gauge32
			MAX-ACCESS	read-only
			STATUS	current
			::= { hmWanMbus78 2 }

hmWanMbus78Version		OBJECT-TYPE
			SYNTAX	Gauge32
			MAX-ACCESS	read-only
			STATUS	current
			::= { hmWanMbus78 3 }

hmWanMbus78Medium		OBJECT-TYPE
			SYNTAX	Gauge32
			MAX-ACCESS	read-only
			STATUS	current
			::= { hmWanMbus78 4 }

hmWanMbus78Status		OBJECT-TYPE
			SYNTAX	Gauge32
			MAX-ACCESS	read-only
			STATUS	current
			::= { hmWanMbus78 5 }

hmWanMbus78VIF00		OBJECT-TYPE
			SYNTAX	INTEGER
			MAX-ACCESS	read-only
			STATUS	current
			::= { hmWanMbus78 6 }

hmWanMbus78Value00		OBJECT-TYPE
			SYNTAX	INTEGER
			MAX-ACCESS	read-only
			STATUS	current
			::= { hmWanMbus78 7 }

hmWanMbus78VIF01		OBJECT-TYPE
			SYNTAX	INTEGER
			MAX-ACCESS	read-only
			STATUS	current
			::= { hmWanMbus78 8 }

hmWanMbus78Value01		OBJECT-TYPE
			SYNTAX	INTEGER
			MAX-ACCESS	read-only
			STATUS	current
			::= { hmWanMbus78 9 }

hmWanMbus78VIF02		OBJECT-TYPE
			SYNTAX	INTEGER
			MAX-ACCESS	read-only
			STATUS	current
			::= { hmWanMbus78 10 }

hmWanMbus78Value02		OBJECT-TYPE
			SYNTAX	INTEGER
			MAX-ACCESS	read-only
			STATUS	current
			::= { hmWanMbus78 11 }

hmWanMbus78VIF03		OBJECT-TYPE
			SYNTAX	INTEGER
			MAX-ACCESS	read-only
			STATUS	current
			::= { hmWanMbus78 12 }

hmWanMbus78Value03		OBJECT-TYPE
			SYNTAX	INTEGER
			MAX-ACCESS	read-only
			STATUS	current
			::= { hmWanMbus78 13 }

hmWanMbus78VIF04		OBJECT-TYPE
			SYNTAX	INTEGER
			MAX-ACCESS	read-only
			STATUS	current
			::= { hmWanMbus78 14 }

hmWanMbus78Value04		OBJECT-TYPE
			SYNTAX	INTEGER
			MAX-ACCESS	read-only
			STATUS	current
			::= { hmWanMbus78 15 }

hmWanMbus78VIF05		OBJECT-TYPE
			SYNTAX	INTEGER
			MAX-ACCESS	read-only
			STATUS	current
			::= { hmWanMbus78 16 }

hmWanMbus78Value05		OBJECT-TYPE
			SYNTAX	INTEGER
			MAX-ACCESS	read-only
			STATUS	current
			::= { hmWanMbus78 17 }

hmWanMbus78VIF06		OBJECT-TYPE
			SYNTAX	INTEGER
			MAX-ACCESS	read-only
			STATUS	current
			::= { hmWanMbus78 18 }

hmWanMbus78Value06		OBJECT-TYPE
			SYNTAX	INTEGER
			MAX-ACCESS	read-only
			STATUS	current
			::= { hmWanMbus78 19 }

hmWanMbus78VIF07		OBJECT-TYPE
			SYNTAX	INTEGER
			MAX-ACCESS	read-only
			STATUS	current
			::= { hmWanMbus78 20 }

hmWanMbus78Value07		OBJECT-TYPE
			SYNTAX	INTEGER
			MAX-ACCESS	read-only
			STATUS	current
			::= { hmWanMbus78 21 }

hmWanMbus78VIF08		OBJECT-TYPE
			SYNTAX	INTEGER
			MAX-ACCESS	read-only
			STATUS	current
			::= { hmWanMbus78 22 }

hmWanMbus78Value08		OBJECT-TYPE
			SYNTAX	INTEGER
			MAX-ACCESS	read-only
			STATUS	current
			::= { hmWanMbus78 23 }

hmWanMbus78VIF09		OBJECT-TYPE
			SYNTAX	INTEGER
			MAX-ACCESS	read-only
			STATUS	current
			::= { hmWanMbus78 24 }

hmWanMbus78Value09		OBJECT-TYPE
			SYNTAX	INTEGER
			MAX-ACCESS	read-only
			STATUS	current
			::= { hmWanMbus78 25 }

hmWanMbus78VIF0A		OBJECT-TYPE
			SYNTAX	INTEGER
			MAX-ACCESS	read-only
			STATUS	current
			::= { hmWanMbus78 26 }

hmWanMbus78Value0A		OBJECT-TYPE
			SYNTAX	INTEGER
			MAX-ACCESS	read-only
			STATUS	current
			::= { hmWanMbus78 27 }

hmWanMbus78VIF0B		OBJECT-TYPE
			SYNTAX	INTEGER
			MAX-ACCESS	read-only
			STATUS	current
			::= { hmWanMbus78 28 }

hmWanMbus78Value0B		OBJECT-TYPE
			SYNTAX	INTEGER
			MAX-ACCESS	read-only
			STATUS	current
			::= { hmWanMbus78 29 }

hmWanMbus78VIF0C		OBJECT-TYPE
			SYNTAX	INTEGER
			MAX-ACCESS	read-only
			STATUS	current
			::= { hmWanMbus78 30 }

hmWanMbus78Value0C		OBJECT-TYPE
			SYNTAX	INTEGER
			MAX-ACCESS	read-only
			STATUS	current
			::= { hmWanMbus78 31 }

hmWanMbus78VIF0D		OBJECT-TYPE
			SYNTAX	INTEGER
			MAX-ACCESS	read-only
			STATUS	current
			::= { hmWanMbus78 32 }

hmWanMbus78Value0D		OBJECT-TYPE
			SYNTAX	INTEGER
			MAX-ACCESS	read-only
			STATUS	current
			::= { hmWanMbus78 33 }

hmWanMbus78VIF0E		OBJECT-TYPE
			SYNTAX	INTEGER
			MAX-ACCESS	read-only
			STATUS	current
			::= { hmWanMbus78 34 }

hmWanMbus78Value0E		OBJECT-TYPE
			SYNTAX	INTEGER
			MAX-ACCESS	read-only
			STATUS	current
			::= { hmWanMbus78 35 }

hmWanMbus78VIF0F		OBJECT-TYPE
			SYNTAX	INTEGER
			MAX-ACCESS	read-only
			STATUS	current
			::= { hmWanMbus78 36 }

hmWanMbus78Value0F		OBJECT-TYPE
			SYNTAX	INTEGER
			MAX-ACCESS	read-only
			STATUS	current
			::= { hmWanMbus78 37 }

hmWanMbus78VIF10		OBJECT-TYPE
			SYNTAX	INTEGER
			MAX-ACCESS	read-only
			STATUS	current
			::= { hmWanMbus78 38 }

hmWanMbus78Value10		OBJECT-TYPE
			SYNTAX	INTEGER
			MAX-ACCESS	read-only
			STATUS	current
			::= { hmWanMbus78 39 }

hmWanMbus78VIF11		OBJECT-TYPE
			SYNTAX	INTEGER
			MAX-ACCESS	read-only
			STATUS	current
			::= { hmWanMbus78 40 }

hmWanMbus78Value11		OBJECT-TYPE
			SYNTAX	INTEGER
			MAX-ACCESS	read-only
			STATUS	current
			::= { hmWanMbus78 41 }

hmWanMbus78VIF12		OBJECT-TYPE
			SYNTAX	INTEGER
			MAX-ACCESS	read-only
			STATUS	current
			::= { hmWanMbus78 42 }

hmWanMbus78Value12		OBJECT-TYPE
			SYNTAX	INTEGER
			MAX-ACCESS	read-only
			STATUS	current
			::= { hmWanMbus78 43 }

hmWanMbus78VIF13		OBJECT-TYPE
			SYNTAX	INTEGER
			MAX-ACCESS	read-only
			STATUS	current
			::= { hmWanMbus78 44 }

hmWanMbus78Value13		OBJECT-TYPE
			SYNTAX	INTEGER
			MAX-ACCESS	read-only
			STATUS	current
			::= { hmWanMbus78 45 }

hmWanMbus78VIF14		OBJECT-TYPE
			SYNTAX	INTEGER
			MAX-ACCESS	read-only
			STATUS	current
			::= { hmWanMbus78 46 }

hmWanMbus78Value14		OBJECT-TYPE
			SYNTAX	INTEGER
			MAX-ACCESS	read-only
			STATUS	current
			::= { hmWanMbus78 47 }

hmWanMbus78VIF15		OBJECT-TYPE
			SYNTAX	INTEGER
			MAX-ACCESS	read-only
			STATUS	current
			::= { hmWanMbus78 48 }

hmWanMbus78Value15		OBJECT-TYPE
			SYNTAX	INTEGER
			MAX-ACCESS	read-only
			STATUS	current
			::= { hmWanMbus78 49 }

hmWanMbus78VIF16		OBJECT-TYPE
			SYNTAX	INTEGER
			MAX-ACCESS	read-only
			STATUS	current
			::= { hmWanMbus78 50 }

hmWanMbus78Value16		OBJECT-TYPE
			SYNTAX	INTEGER
			MAX-ACCESS	read-only
			STATUS	current
			::= { hmWanMbus78 51 }

hmWanMbus78VIF17		OBJECT-TYPE
			SYNTAX	INTEGER
			MAX-ACCESS	read-only
			STATUS	current
			::= { hmWanMbus78 52 }

hmWanMbus78Value17		OBJECT-TYPE
			SYNTAX	INTEGER
			MAX-ACCESS	read-only
			STATUS	current
			::= { hmWanMbus78 53 }

hmWanMbus78VIF18		OBJECT-TYPE
			SYNTAX	INTEGER
			MAX-ACCESS	read-only
			STATUS	current
			::= { hmWanMbus78 54 }

hmWanMbus78Value18		OBJECT-TYPE
			SYNTAX	INTEGER
			MAX-ACCESS	read-only
			STATUS	current
			::= { hmWanMbus78 55 }

hmWanMbus78VIF19		OBJECT-TYPE
			SYNTAX	INTEGER
			MAX-ACCESS	read-only
			STATUS	current
			::= { hmWanMbus78 56 }

hmWanMbus78Value19		OBJECT-TYPE
			SYNTAX	INTEGER
			MAX-ACCESS	read-only
			STATUS	current
			::= { hmWanMbus78 57 }

hmWanMbus78VIF1A		OBJECT-TYPE
			SYNTAX	INTEGER
			MAX-ACCESS	read-only
			STATUS	current
			::= { hmWanMbus78 58 }

hmWanMbus78Value1A		OBJECT-TYPE
			SYNTAX	INTEGER
			MAX-ACCESS	read-only
			STATUS	current
			::= { hmWanMbus78 59 }

hmWanMbus78VIF1B		OBJECT-TYPE
			SYNTAX	INTEGER
			MAX-ACCESS	read-only
			STATUS	current
			::= { hmWanMbus78 60 }

hmWanMbus78Value1B		OBJECT-TYPE
			SYNTAX	INTEGER
			MAX-ACCESS	read-only
			STATUS	current
			::= { hmWanMbus78 61 }

hmWanMbus78VIF1C		OBJECT-TYPE
			SYNTAX	INTEGER
			MAX-ACCESS	read-only
			STATUS	current
			::= { hmWanMbus78 62 }

hmWanMbus78Value1C		OBJECT-TYPE
			SYNTAX	INTEGER
			MAX-ACCESS	read-only
			STATUS	current
			::= { hmWanMbus78 63 }

hmWanMbus78VIF1D		OBJECT-TYPE
			SYNTAX	INTEGER
			MAX-ACCESS	read-only
			STATUS	current
			::= { hmWanMbus78 64 }

hmWanMbus78Value1D		OBJECT-TYPE
			SYNTAX	INTEGER
			MAX-ACCESS	read-only
			STATUS	current
			::= { hmWanMbus78 65 }

hmWanMbus78VIF1E		OBJECT-TYPE
			SYNTAX	INTEGER
			MAX-ACCESS	read-only
			STATUS	current
			::= { hmWanMbus78 66 }

hmWanMbus78Value1E		OBJECT-TYPE
			SYNTAX	INTEGER
			MAX-ACCESS	read-only
			STATUS	current
			::= { hmWanMbus78 67 }

hmWanMbus78VIF1F		OBJECT-TYPE
			SYNTAX	INTEGER
			MAX-ACCESS	read-only
			STATUS	current
			::= { hmWanMbus78 68 }

hmWanMbus78Value1F		OBJECT-TYPE
			SYNTAX	INTEGER
			MAX-ACCESS	read-only
			STATUS	current
			::= { hmWanMbus78 69 }

hmWanMbus78VIF20		OBJECT-TYPE
			SYNTAX	INTEGER
			MAX-ACCESS	read-only
			STATUS	current
			::= { hmWanMbus78 70 }

hmWanMbus78Value20		OBJECT-TYPE
			SYNTAX	INTEGER
			MAX-ACCESS	read-only
			STATUS	current
			::= { hmWanMbus78 71 }

hmWanMbus78VIF21		OBJECT-TYPE
			SYNTAX	INTEGER
			MAX-ACCESS	read-only
			STATUS	current
			::= { hmWanMbus78 72 }

hmWanMbus78Value21		OBJECT-TYPE
			SYNTAX	INTEGER
			MAX-ACCESS	read-only
			STATUS	current
			::= { hmWanMbus78 73 }

hmWanMbus78VIF22		OBJECT-TYPE
			SYNTAX	INTEGER
			MAX-ACCESS	read-only
			STATUS	current
			::= { hmWanMbus78 74 }

hmWanMbus78Value22		OBJECT-TYPE
			SYNTAX	INTEGER
			MAX-ACCESS	read-only
			STATUS	current
			::= { hmWanMbus78 75 }

hmWanMbus78VIF23		OBJECT-TYPE
			SYNTAX	INTEGER
			MAX-ACCESS	read-only
			STATUS	current
			::= { hmWanMbus78 76 }

hmWanMbus78Value23		OBJECT-TYPE
			SYNTAX	INTEGER
			MAX-ACCESS	read-only
			STATUS	current
			::= { hmWanMbus78 77 }

hmWanMbus78VIF24		OBJECT-TYPE
			SYNTAX	INTEGER
			MAX-ACCESS	read-only
			STATUS	current
			::= { hmWanMbus78 78 }

hmWanMbus78Value24		OBJECT-TYPE
			SYNTAX	INTEGER
			MAX-ACCESS	read-only
			STATUS	current
			::= { hmWanMbus78 79 }

hmWanMbus78VIF25		OBJECT-TYPE
			SYNTAX	INTEGER
			MAX-ACCESS	read-only
			STATUS	current
			::= { hmWanMbus78 80 }

hmWanMbus78Value25		OBJECT-TYPE
			SYNTAX	INTEGER
			MAX-ACCESS	read-only
			STATUS	current
			::= { hmWanMbus78 81 }

hmWanMbus78VIF26		OBJECT-TYPE
			SYNTAX	INTEGER
			MAX-ACCESS	read-only
			STATUS	current
			::= { hmWanMbus78 82 }

hmWanMbus78Value26		OBJECT-TYPE
			SYNTAX	INTEGER
			MAX-ACCESS	read-only
			STATUS	current
			::= { hmWanMbus78 83 }

hmWanMbus78VIF27		OBJECT-TYPE
			SYNTAX	INTEGER
			MAX-ACCESS	read-only
			STATUS	current
			::= { hmWanMbus78 84 }

hmWanMbus78Value27		OBJECT-TYPE
			SYNTAX	INTEGER
			MAX-ACCESS	read-only
			STATUS	current
			::= { hmWanMbus78 85 }

hmWanMbus78VIF28		OBJECT-TYPE
			SYNTAX	INTEGER
			MAX-ACCESS	read-only
			STATUS	current
			::= { hmWanMbus78 86 }

hmWanMbus78Value28		OBJECT-TYPE
			SYNTAX	INTEGER
			MAX-ACCESS	read-only
			STATUS	current
			::= { hmWanMbus78 87 }

hmWanMbus78VIF29		OBJECT-TYPE
			SYNTAX	INTEGER
			MAX-ACCESS	read-only
			STATUS	current
			::= { hmWanMbus78 88 }

hmWanMbus78Value29		OBJECT-TYPE
			SYNTAX	INTEGER
			MAX-ACCESS	read-only
			STATUS	current
			::= { hmWanMbus78 89 }

hmWanMbus78VIF2A		OBJECT-TYPE
			SYNTAX	INTEGER
			MAX-ACCESS	read-only
			STATUS	current
			::= { hmWanMbus78 90 }

hmWanMbus78Value2A		OBJECT-TYPE
			SYNTAX	INTEGER
			MAX-ACCESS	read-only
			STATUS	current
			::= { hmWanMbus78 91 }

hmWanMbus78VIF2B		OBJECT-TYPE
			SYNTAX	INTEGER
			MAX-ACCESS	read-only
			STATUS	current
			::= { hmWanMbus78 92 }

hmWanMbus78Value2B		OBJECT-TYPE
			SYNTAX	INTEGER
			MAX-ACCESS	read-only
			STATUS	current
			::= { hmWanMbus78 93 }

hmWanMbus78VIF2C		OBJECT-TYPE
			SYNTAX	INTEGER
			MAX-ACCESS	read-only
			STATUS	current
			::= { hmWanMbus78 94 }

hmWanMbus78Value2C		OBJECT-TYPE
			SYNTAX	INTEGER
			MAX-ACCESS	read-only
			STATUS	current
			::= { hmWanMbus78 95 }

hmWanMbus78VIF2D		OBJECT-TYPE
			SYNTAX	INTEGER
			MAX-ACCESS	read-only
			STATUS	current
			::= { hmWanMbus78 96 }

hmWanMbus78Value2D		OBJECT-TYPE
			SYNTAX	INTEGER
			MAX-ACCESS	read-only
			STATUS	current
			::= { hmWanMbus78 97 }

hmWanMbus78VIF2E		OBJECT-TYPE
			SYNTAX	INTEGER
			MAX-ACCESS	read-only
			STATUS	current
			::= { hmWanMbus78 98 }

hmWanMbus78Value2E		OBJECT-TYPE
			SYNTAX	INTEGER
			MAX-ACCESS	read-only
			STATUS	current
			::= { hmWanMbus78 99 }

hmWanMbus78VIF2F		OBJECT-TYPE
			SYNTAX	INTEGER
			MAX-ACCESS	read-only
			STATUS	current
			::= { hmWanMbus78 100 }

hmWanMbus78Value2F		OBJECT-TYPE
			SYNTAX	INTEGER
			MAX-ACCESS	read-only
			STATUS	current
			::= { hmWanMbus78 101 }

hmWanMbus79			OBJECT IDENTIFIER ::= { hmWanMbus 121 }

hmWanMbus79IdNumber		OBJECT-TYPE
			SYNTAX	Gauge32
			MAX-ACCESS	read-only
			STATUS	current
			::= { hmWanMbus79 1 }

hmWanMbus79Manufacturer	OBJECT-TYPE
			SYNTAX	Gauge32
			MAX-ACCESS	read-only
			STATUS	current
			::= { hmWanMbus79 2 }

hmWanMbus79Version		OBJECT-TYPE
			SYNTAX	Gauge32
			MAX-ACCESS	read-only
			STATUS	current
			::= { hmWanMbus79 3 }

hmWanMbus79Medium		OBJECT-TYPE
			SYNTAX	Gauge32
			MAX-ACCESS	read-only
			STATUS	current
			::= { hmWanMbus79 4 }

hmWanMbus79Status		OBJECT-TYPE
			SYNTAX	Gauge32
			MAX-ACCESS	read-only
			STATUS	current
			::= { hmWanMbus79 5 }

hmWanMbus79VIF00		OBJECT-TYPE
			SYNTAX	INTEGER
			MAX-ACCESS	read-only
			STATUS	current
			::= { hmWanMbus79 6 }

hmWanMbus79Value00		OBJECT-TYPE
			SYNTAX	INTEGER
			MAX-ACCESS	read-only
			STATUS	current
			::= { hmWanMbus79 7 }

hmWanMbus79VIF01		OBJECT-TYPE
			SYNTAX	INTEGER
			MAX-ACCESS	read-only
			STATUS	current
			::= { hmWanMbus79 8 }

hmWanMbus79Value01		OBJECT-TYPE
			SYNTAX	INTEGER
			MAX-ACCESS	read-only
			STATUS	current
			::= { hmWanMbus79 9 }

hmWanMbus79VIF02		OBJECT-TYPE
			SYNTAX	INTEGER
			MAX-ACCESS	read-only
			STATUS	current
			::= { hmWanMbus79 10 }

hmWanMbus79Value02		OBJECT-TYPE
			SYNTAX	INTEGER
			MAX-ACCESS	read-only
			STATUS	current
			::= { hmWanMbus79 11 }

hmWanMbus79VIF03		OBJECT-TYPE
			SYNTAX	INTEGER
			MAX-ACCESS	read-only
			STATUS	current
			::= { hmWanMbus79 12 }

hmWanMbus79Value03		OBJECT-TYPE
			SYNTAX	INTEGER
			MAX-ACCESS	read-only
			STATUS	current
			::= { hmWanMbus79 13 }

hmWanMbus79VIF04		OBJECT-TYPE
			SYNTAX	INTEGER
			MAX-ACCESS	read-only
			STATUS	current
			::= { hmWanMbus79 14 }

hmWanMbus79Value04		OBJECT-TYPE
			SYNTAX	INTEGER
			MAX-ACCESS	read-only
			STATUS	current
			::= { hmWanMbus79 15 }

hmWanMbus79VIF05		OBJECT-TYPE
			SYNTAX	INTEGER
			MAX-ACCESS	read-only
			STATUS	current
			::= { hmWanMbus79 16 }

hmWanMbus79Value05		OBJECT-TYPE
			SYNTAX	INTEGER
			MAX-ACCESS	read-only
			STATUS	current
			::= { hmWanMbus79 17 }

hmWanMbus79VIF06		OBJECT-TYPE
			SYNTAX	INTEGER
			MAX-ACCESS	read-only
			STATUS	current
			::= { hmWanMbus79 18 }

hmWanMbus79Value06		OBJECT-TYPE
			SYNTAX	INTEGER
			MAX-ACCESS	read-only
			STATUS	current
			::= { hmWanMbus79 19 }

hmWanMbus79VIF07		OBJECT-TYPE
			SYNTAX	INTEGER
			MAX-ACCESS	read-only
			STATUS	current
			::= { hmWanMbus79 20 }

hmWanMbus79Value07		OBJECT-TYPE
			SYNTAX	INTEGER
			MAX-ACCESS	read-only
			STATUS	current
			::= { hmWanMbus79 21 }

hmWanMbus79VIF08		OBJECT-TYPE
			SYNTAX	INTEGER
			MAX-ACCESS	read-only
			STATUS	current
			::= { hmWanMbus79 22 }

hmWanMbus79Value08		OBJECT-TYPE
			SYNTAX	INTEGER
			MAX-ACCESS	read-only
			STATUS	current
			::= { hmWanMbus79 23 }

hmWanMbus79VIF09		OBJECT-TYPE
			SYNTAX	INTEGER
			MAX-ACCESS	read-only
			STATUS	current
			::= { hmWanMbus79 24 }

hmWanMbus79Value09		OBJECT-TYPE
			SYNTAX	INTEGER
			MAX-ACCESS	read-only
			STATUS	current
			::= { hmWanMbus79 25 }

hmWanMbus79VIF0A		OBJECT-TYPE
			SYNTAX	INTEGER
			MAX-ACCESS	read-only
			STATUS	current
			::= { hmWanMbus79 26 }

hmWanMbus79Value0A		OBJECT-TYPE
			SYNTAX	INTEGER
			MAX-ACCESS	read-only
			STATUS	current
			::= { hmWanMbus79 27 }

hmWanMbus79VIF0B		OBJECT-TYPE
			SYNTAX	INTEGER
			MAX-ACCESS	read-only
			STATUS	current
			::= { hmWanMbus79 28 }

hmWanMbus79Value0B		OBJECT-TYPE
			SYNTAX	INTEGER
			MAX-ACCESS	read-only
			STATUS	current
			::= { hmWanMbus79 29 }

hmWanMbus79VIF0C		OBJECT-TYPE
			SYNTAX	INTEGER
			MAX-ACCESS	read-only
			STATUS	current
			::= { hmWanMbus79 30 }

hmWanMbus79Value0C		OBJECT-TYPE
			SYNTAX	INTEGER
			MAX-ACCESS	read-only
			STATUS	current
			::= { hmWanMbus79 31 }

hmWanMbus79VIF0D		OBJECT-TYPE
			SYNTAX	INTEGER
			MAX-ACCESS	read-only
			STATUS	current
			::= { hmWanMbus79 32 }

hmWanMbus79Value0D		OBJECT-TYPE
			SYNTAX	INTEGER
			MAX-ACCESS	read-only
			STATUS	current
			::= { hmWanMbus79 33 }

hmWanMbus79VIF0E		OBJECT-TYPE
			SYNTAX	INTEGER
			MAX-ACCESS	read-only
			STATUS	current
			::= { hmWanMbus79 34 }

hmWanMbus79Value0E		OBJECT-TYPE
			SYNTAX	INTEGER
			MAX-ACCESS	read-only
			STATUS	current
			::= { hmWanMbus79 35 }

hmWanMbus79VIF0F		OBJECT-TYPE
			SYNTAX	INTEGER
			MAX-ACCESS	read-only
			STATUS	current
			::= { hmWanMbus79 36 }

hmWanMbus79Value0F		OBJECT-TYPE
			SYNTAX	INTEGER
			MAX-ACCESS	read-only
			STATUS	current
			::= { hmWanMbus79 37 }

hmWanMbus79VIF10		OBJECT-TYPE
			SYNTAX	INTEGER
			MAX-ACCESS	read-only
			STATUS	current
			::= { hmWanMbus79 38 }

hmWanMbus79Value10		OBJECT-TYPE
			SYNTAX	INTEGER
			MAX-ACCESS	read-only
			STATUS	current
			::= { hmWanMbus79 39 }

hmWanMbus79VIF11		OBJECT-TYPE
			SYNTAX	INTEGER
			MAX-ACCESS	read-only
			STATUS	current
			::= { hmWanMbus79 40 }

hmWanMbus79Value11		OBJECT-TYPE
			SYNTAX	INTEGER
			MAX-ACCESS	read-only
			STATUS	current
			::= { hmWanMbus79 41 }

hmWanMbus79VIF12		OBJECT-TYPE
			SYNTAX	INTEGER
			MAX-ACCESS	read-only
			STATUS	current
			::= { hmWanMbus79 42 }

hmWanMbus79Value12		OBJECT-TYPE
			SYNTAX	INTEGER
			MAX-ACCESS	read-only
			STATUS	current
			::= { hmWanMbus79 43 }

hmWanMbus79VIF13		OBJECT-TYPE
			SYNTAX	INTEGER
			MAX-ACCESS	read-only
			STATUS	current
			::= { hmWanMbus79 44 }

hmWanMbus79Value13		OBJECT-TYPE
			SYNTAX	INTEGER
			MAX-ACCESS	read-only
			STATUS	current
			::= { hmWanMbus79 45 }

hmWanMbus79VIF14		OBJECT-TYPE
			SYNTAX	INTEGER
			MAX-ACCESS	read-only
			STATUS	current
			::= { hmWanMbus79 46 }

hmWanMbus79Value14		OBJECT-TYPE
			SYNTAX	INTEGER
			MAX-ACCESS	read-only
			STATUS	current
			::= { hmWanMbus79 47 }

hmWanMbus79VIF15		OBJECT-TYPE
			SYNTAX	INTEGER
			MAX-ACCESS	read-only
			STATUS	current
			::= { hmWanMbus79 48 }

hmWanMbus79Value15		OBJECT-TYPE
			SYNTAX	INTEGER
			MAX-ACCESS	read-only
			STATUS	current
			::= { hmWanMbus79 49 }

hmWanMbus79VIF16		OBJECT-TYPE
			SYNTAX	INTEGER
			MAX-ACCESS	read-only
			STATUS	current
			::= { hmWanMbus79 50 }

hmWanMbus79Value16		OBJECT-TYPE
			SYNTAX	INTEGER
			MAX-ACCESS	read-only
			STATUS	current
			::= { hmWanMbus79 51 }

hmWanMbus79VIF17		OBJECT-TYPE
			SYNTAX	INTEGER
			MAX-ACCESS	read-only
			STATUS	current
			::= { hmWanMbus79 52 }

hmWanMbus79Value17		OBJECT-TYPE
			SYNTAX	INTEGER
			MAX-ACCESS	read-only
			STATUS	current
			::= { hmWanMbus79 53 }

hmWanMbus79VIF18		OBJECT-TYPE
			SYNTAX	INTEGER
			MAX-ACCESS	read-only
			STATUS	current
			::= { hmWanMbus79 54 }

hmWanMbus79Value18		OBJECT-TYPE
			SYNTAX	INTEGER
			MAX-ACCESS	read-only
			STATUS	current
			::= { hmWanMbus79 55 }

hmWanMbus79VIF19		OBJECT-TYPE
			SYNTAX	INTEGER
			MAX-ACCESS	read-only
			STATUS	current
			::= { hmWanMbus79 56 }

hmWanMbus79Value19		OBJECT-TYPE
			SYNTAX	INTEGER
			MAX-ACCESS	read-only
			STATUS	current
			::= { hmWanMbus79 57 }

hmWanMbus79VIF1A		OBJECT-TYPE
			SYNTAX	INTEGER
			MAX-ACCESS	read-only
			STATUS	current
			::= { hmWanMbus79 58 }

hmWanMbus79Value1A		OBJECT-TYPE
			SYNTAX	INTEGER
			MAX-ACCESS	read-only
			STATUS	current
			::= { hmWanMbus79 59 }

hmWanMbus79VIF1B		OBJECT-TYPE
			SYNTAX	INTEGER
			MAX-ACCESS	read-only
			STATUS	current
			::= { hmWanMbus79 60 }

hmWanMbus79Value1B		OBJECT-TYPE
			SYNTAX	INTEGER
			MAX-ACCESS	read-only
			STATUS	current
			::= { hmWanMbus79 61 }

hmWanMbus79VIF1C		OBJECT-TYPE
			SYNTAX	INTEGER
			MAX-ACCESS	read-only
			STATUS	current
			::= { hmWanMbus79 62 }

hmWanMbus79Value1C		OBJECT-TYPE
			SYNTAX	INTEGER
			MAX-ACCESS	read-only
			STATUS	current
			::= { hmWanMbus79 63 }

hmWanMbus79VIF1D		OBJECT-TYPE
			SYNTAX	INTEGER
			MAX-ACCESS	read-only
			STATUS	current
			::= { hmWanMbus79 64 }

hmWanMbus79Value1D		OBJECT-TYPE
			SYNTAX	INTEGER
			MAX-ACCESS	read-only
			STATUS	current
			::= { hmWanMbus79 65 }

hmWanMbus79VIF1E		OBJECT-TYPE
			SYNTAX	INTEGER
			MAX-ACCESS	read-only
			STATUS	current
			::= { hmWanMbus79 66 }

hmWanMbus79Value1E		OBJECT-TYPE
			SYNTAX	INTEGER
			MAX-ACCESS	read-only
			STATUS	current
			::= { hmWanMbus79 67 }

hmWanMbus79VIF1F		OBJECT-TYPE
			SYNTAX	INTEGER
			MAX-ACCESS	read-only
			STATUS	current
			::= { hmWanMbus79 68 }

hmWanMbus79Value1F		OBJECT-TYPE
			SYNTAX	INTEGER
			MAX-ACCESS	read-only
			STATUS	current
			::= { hmWanMbus79 69 }

hmWanMbus79VIF20		OBJECT-TYPE
			SYNTAX	INTEGER
			MAX-ACCESS	read-only
			STATUS	current
			::= { hmWanMbus79 70 }

hmWanMbus79Value20		OBJECT-TYPE
			SYNTAX	INTEGER
			MAX-ACCESS	read-only
			STATUS	current
			::= { hmWanMbus79 71 }

hmWanMbus79VIF21		OBJECT-TYPE
			SYNTAX	INTEGER
			MAX-ACCESS	read-only
			STATUS	current
			::= { hmWanMbus79 72 }

hmWanMbus79Value21		OBJECT-TYPE
			SYNTAX	INTEGER
			MAX-ACCESS	read-only
			STATUS	current
			::= { hmWanMbus79 73 }

hmWanMbus79VIF22		OBJECT-TYPE
			SYNTAX	INTEGER
			MAX-ACCESS	read-only
			STATUS	current
			::= { hmWanMbus79 74 }

hmWanMbus79Value22		OBJECT-TYPE
			SYNTAX	INTEGER
			MAX-ACCESS	read-only
			STATUS	current
			::= { hmWanMbus79 75 }

hmWanMbus79VIF23		OBJECT-TYPE
			SYNTAX	INTEGER
			MAX-ACCESS	read-only
			STATUS	current
			::= { hmWanMbus79 76 }

hmWanMbus79Value23		OBJECT-TYPE
			SYNTAX	INTEGER
			MAX-ACCESS	read-only
			STATUS	current
			::= { hmWanMbus79 77 }

hmWanMbus79VIF24		OBJECT-TYPE
			SYNTAX	INTEGER
			MAX-ACCESS	read-only
			STATUS	current
			::= { hmWanMbus79 78 }

hmWanMbus79Value24		OBJECT-TYPE
			SYNTAX	INTEGER
			MAX-ACCESS	read-only
			STATUS	current
			::= { hmWanMbus79 79 }

hmWanMbus79VIF25		OBJECT-TYPE
			SYNTAX	INTEGER
			MAX-ACCESS	read-only
			STATUS	current
			::= { hmWanMbus79 80 }

hmWanMbus79Value25		OBJECT-TYPE
			SYNTAX	INTEGER
			MAX-ACCESS	read-only
			STATUS	current
			::= { hmWanMbus79 81 }

hmWanMbus79VIF26		OBJECT-TYPE
			SYNTAX	INTEGER
			MAX-ACCESS	read-only
			STATUS	current
			::= { hmWanMbus79 82 }

hmWanMbus79Value26		OBJECT-TYPE
			SYNTAX	INTEGER
			MAX-ACCESS	read-only
			STATUS	current
			::= { hmWanMbus79 83 }

hmWanMbus79VIF27		OBJECT-TYPE
			SYNTAX	INTEGER
			MAX-ACCESS	read-only
			STATUS	current
			::= { hmWanMbus79 84 }

hmWanMbus79Value27		OBJECT-TYPE
			SYNTAX	INTEGER
			MAX-ACCESS	read-only
			STATUS	current
			::= { hmWanMbus79 85 }

hmWanMbus79VIF28		OBJECT-TYPE
			SYNTAX	INTEGER
			MAX-ACCESS	read-only
			STATUS	current
			::= { hmWanMbus79 86 }

hmWanMbus79Value28		OBJECT-TYPE
			SYNTAX	INTEGER
			MAX-ACCESS	read-only
			STATUS	current
			::= { hmWanMbus79 87 }

hmWanMbus79VIF29		OBJECT-TYPE
			SYNTAX	INTEGER
			MAX-ACCESS	read-only
			STATUS	current
			::= { hmWanMbus79 88 }

hmWanMbus79Value29		OBJECT-TYPE
			SYNTAX	INTEGER
			MAX-ACCESS	read-only
			STATUS	current
			::= { hmWanMbus79 89 }

hmWanMbus79VIF2A		OBJECT-TYPE
			SYNTAX	INTEGER
			MAX-ACCESS	read-only
			STATUS	current
			::= { hmWanMbus79 90 }

hmWanMbus79Value2A		OBJECT-TYPE
			SYNTAX	INTEGER
			MAX-ACCESS	read-only
			STATUS	current
			::= { hmWanMbus79 91 }

hmWanMbus79VIF2B		OBJECT-TYPE
			SYNTAX	INTEGER
			MAX-ACCESS	read-only
			STATUS	current
			::= { hmWanMbus79 92 }

hmWanMbus79Value2B		OBJECT-TYPE
			SYNTAX	INTEGER
			MAX-ACCESS	read-only
			STATUS	current
			::= { hmWanMbus79 93 }

hmWanMbus79VIF2C		OBJECT-TYPE
			SYNTAX	INTEGER
			MAX-ACCESS	read-only
			STATUS	current
			::= { hmWanMbus79 94 }

hmWanMbus79Value2C		OBJECT-TYPE
			SYNTAX	INTEGER
			MAX-ACCESS	read-only
			STATUS	current
			::= { hmWanMbus79 95 }

hmWanMbus79VIF2D		OBJECT-TYPE
			SYNTAX	INTEGER
			MAX-ACCESS	read-only
			STATUS	current
			::= { hmWanMbus79 96 }

hmWanMbus79Value2D		OBJECT-TYPE
			SYNTAX	INTEGER
			MAX-ACCESS	read-only
			STATUS	current
			::= { hmWanMbus79 97 }

hmWanMbus79VIF2E		OBJECT-TYPE
			SYNTAX	INTEGER
			MAX-ACCESS	read-only
			STATUS	current
			::= { hmWanMbus79 98 }

hmWanMbus79Value2E		OBJECT-TYPE
			SYNTAX	INTEGER
			MAX-ACCESS	read-only
			STATUS	current
			::= { hmWanMbus79 99 }

hmWanMbus79VIF2F		OBJECT-TYPE
			SYNTAX	INTEGER
			MAX-ACCESS	read-only
			STATUS	current
			::= { hmWanMbus79 100 }

hmWanMbus79Value2F		OBJECT-TYPE
			SYNTAX	INTEGER
			MAX-ACCESS	read-only
			STATUS	current
			::= { hmWanMbus79 101 }

hmWanMbus7A			OBJECT IDENTIFIER ::= { hmWanMbus 122 }

hmWanMbus7AIdNumber		OBJECT-TYPE
			SYNTAX	Gauge32
			MAX-ACCESS	read-only
			STATUS	current
			::= { hmWanMbus7A 1 }

hmWanMbus7AManufacturer	OBJECT-TYPE
			SYNTAX	Gauge32
			MAX-ACCESS	read-only
			STATUS	current
			::= { hmWanMbus7A 2 }

hmWanMbus7AVersion		OBJECT-TYPE
			SYNTAX	Gauge32
			MAX-ACCESS	read-only
			STATUS	current
			::= { hmWanMbus7A 3 }

hmWanMbus7AMedium		OBJECT-TYPE
			SYNTAX	Gauge32
			MAX-ACCESS	read-only
			STATUS	current
			::= { hmWanMbus7A 4 }

hmWanMbus7AStatus		OBJECT-TYPE
			SYNTAX	Gauge32
			MAX-ACCESS	read-only
			STATUS	current
			::= { hmWanMbus7A 5 }

hmWanMbus7AVIF00		OBJECT-TYPE
			SYNTAX	INTEGER
			MAX-ACCESS	read-only
			STATUS	current
			::= { hmWanMbus7A 6 }

hmWanMbus7AValue00		OBJECT-TYPE
			SYNTAX	INTEGER
			MAX-ACCESS	read-only
			STATUS	current
			::= { hmWanMbus7A 7 }

hmWanMbus7AVIF01		OBJECT-TYPE
			SYNTAX	INTEGER
			MAX-ACCESS	read-only
			STATUS	current
			::= { hmWanMbus7A 8 }

hmWanMbus7AValue01		OBJECT-TYPE
			SYNTAX	INTEGER
			MAX-ACCESS	read-only
			STATUS	current
			::= { hmWanMbus7A 9 }

hmWanMbus7AVIF02		OBJECT-TYPE
			SYNTAX	INTEGER
			MAX-ACCESS	read-only
			STATUS	current
			::= { hmWanMbus7A 10 }

hmWanMbus7AValue02		OBJECT-TYPE
			SYNTAX	INTEGER
			MAX-ACCESS	read-only
			STATUS	current
			::= { hmWanMbus7A 11 }

hmWanMbus7AVIF03		OBJECT-TYPE
			SYNTAX	INTEGER
			MAX-ACCESS	read-only
			STATUS	current
			::= { hmWanMbus7A 12 }

hmWanMbus7AValue03		OBJECT-TYPE
			SYNTAX	INTEGER
			MAX-ACCESS	read-only
			STATUS	current
			::= { hmWanMbus7A 13 }

hmWanMbus7AVIF04		OBJECT-TYPE
			SYNTAX	INTEGER
			MAX-ACCESS	read-only
			STATUS	current
			::= { hmWanMbus7A 14 }

hmWanMbus7AValue04		OBJECT-TYPE
			SYNTAX	INTEGER
			MAX-ACCESS	read-only
			STATUS	current
			::= { hmWanMbus7A 15 }

hmWanMbus7AVIF05		OBJECT-TYPE
			SYNTAX	INTEGER
			MAX-ACCESS	read-only
			STATUS	current
			::= { hmWanMbus7A 16 }

hmWanMbus7AValue05		OBJECT-TYPE
			SYNTAX	INTEGER
			MAX-ACCESS	read-only
			STATUS	current
			::= { hmWanMbus7A 17 }

hmWanMbus7AVIF06		OBJECT-TYPE
			SYNTAX	INTEGER
			MAX-ACCESS	read-only
			STATUS	current
			::= { hmWanMbus7A 18 }

hmWanMbus7AValue06		OBJECT-TYPE
			SYNTAX	INTEGER
			MAX-ACCESS	read-only
			STATUS	current
			::= { hmWanMbus7A 19 }

hmWanMbus7AVIF07		OBJECT-TYPE
			SYNTAX	INTEGER
			MAX-ACCESS	read-only
			STATUS	current
			::= { hmWanMbus7A 20 }

hmWanMbus7AValue07		OBJECT-TYPE
			SYNTAX	INTEGER
			MAX-ACCESS	read-only
			STATUS	current
			::= { hmWanMbus7A 21 }

hmWanMbus7AVIF08		OBJECT-TYPE
			SYNTAX	INTEGER
			MAX-ACCESS	read-only
			STATUS	current
			::= { hmWanMbus7A 22 }

hmWanMbus7AValue08		OBJECT-TYPE
			SYNTAX	INTEGER
			MAX-ACCESS	read-only
			STATUS	current
			::= { hmWanMbus7A 23 }

hmWanMbus7AVIF09		OBJECT-TYPE
			SYNTAX	INTEGER
			MAX-ACCESS	read-only
			STATUS	current
			::= { hmWanMbus7A 24 }

hmWanMbus7AValue09		OBJECT-TYPE
			SYNTAX	INTEGER
			MAX-ACCESS	read-only
			STATUS	current
			::= { hmWanMbus7A 25 }

hmWanMbus7AVIF0A		OBJECT-TYPE
			SYNTAX	INTEGER
			MAX-ACCESS	read-only
			STATUS	current
			::= { hmWanMbus7A 26 }

hmWanMbus7AValue0A		OBJECT-TYPE
			SYNTAX	INTEGER
			MAX-ACCESS	read-only
			STATUS	current
			::= { hmWanMbus7A 27 }

hmWanMbus7AVIF0B		OBJECT-TYPE
			SYNTAX	INTEGER
			MAX-ACCESS	read-only
			STATUS	current
			::= { hmWanMbus7A 28 }

hmWanMbus7AValue0B		OBJECT-TYPE
			SYNTAX	INTEGER
			MAX-ACCESS	read-only
			STATUS	current
			::= { hmWanMbus7A 29 }

hmWanMbus7AVIF0C		OBJECT-TYPE
			SYNTAX	INTEGER
			MAX-ACCESS	read-only
			STATUS	current
			::= { hmWanMbus7A 30 }

hmWanMbus7AValue0C		OBJECT-TYPE
			SYNTAX	INTEGER
			MAX-ACCESS	read-only
			STATUS	current
			::= { hmWanMbus7A 31 }

hmWanMbus7AVIF0D		OBJECT-TYPE
			SYNTAX	INTEGER
			MAX-ACCESS	read-only
			STATUS	current
			::= { hmWanMbus7A 32 }

hmWanMbus7AValue0D		OBJECT-TYPE
			SYNTAX	INTEGER
			MAX-ACCESS	read-only
			STATUS	current
			::= { hmWanMbus7A 33 }

hmWanMbus7AVIF0E		OBJECT-TYPE
			SYNTAX	INTEGER
			MAX-ACCESS	read-only
			STATUS	current
			::= { hmWanMbus7A 34 }

hmWanMbus7AValue0E		OBJECT-TYPE
			SYNTAX	INTEGER
			MAX-ACCESS	read-only
			STATUS	current
			::= { hmWanMbus7A 35 }

hmWanMbus7AVIF0F		OBJECT-TYPE
			SYNTAX	INTEGER
			MAX-ACCESS	read-only
			STATUS	current
			::= { hmWanMbus7A 36 }

hmWanMbus7AValue0F		OBJECT-TYPE
			SYNTAX	INTEGER
			MAX-ACCESS	read-only
			STATUS	current
			::= { hmWanMbus7A 37 }

hmWanMbus7AVIF10		OBJECT-TYPE
			SYNTAX	INTEGER
			MAX-ACCESS	read-only
			STATUS	current
			::= { hmWanMbus7A 38 }

hmWanMbus7AValue10		OBJECT-TYPE
			SYNTAX	INTEGER
			MAX-ACCESS	read-only
			STATUS	current
			::= { hmWanMbus7A 39 }

hmWanMbus7AVIF11		OBJECT-TYPE
			SYNTAX	INTEGER
			MAX-ACCESS	read-only
			STATUS	current
			::= { hmWanMbus7A 40 }

hmWanMbus7AValue11		OBJECT-TYPE
			SYNTAX	INTEGER
			MAX-ACCESS	read-only
			STATUS	current
			::= { hmWanMbus7A 41 }

hmWanMbus7AVIF12		OBJECT-TYPE
			SYNTAX	INTEGER
			MAX-ACCESS	read-only
			STATUS	current
			::= { hmWanMbus7A 42 }

hmWanMbus7AValue12		OBJECT-TYPE
			SYNTAX	INTEGER
			MAX-ACCESS	read-only
			STATUS	current
			::= { hmWanMbus7A 43 }

hmWanMbus7AVIF13		OBJECT-TYPE
			SYNTAX	INTEGER
			MAX-ACCESS	read-only
			STATUS	current
			::= { hmWanMbus7A 44 }

hmWanMbus7AValue13		OBJECT-TYPE
			SYNTAX	INTEGER
			MAX-ACCESS	read-only
			STATUS	current
			::= { hmWanMbus7A 45 }

hmWanMbus7AVIF14		OBJECT-TYPE
			SYNTAX	INTEGER
			MAX-ACCESS	read-only
			STATUS	current
			::= { hmWanMbus7A 46 }

hmWanMbus7AValue14		OBJECT-TYPE
			SYNTAX	INTEGER
			MAX-ACCESS	read-only
			STATUS	current
			::= { hmWanMbus7A 47 }

hmWanMbus7AVIF15		OBJECT-TYPE
			SYNTAX	INTEGER
			MAX-ACCESS	read-only
			STATUS	current
			::= { hmWanMbus7A 48 }

hmWanMbus7AValue15		OBJECT-TYPE
			SYNTAX	INTEGER
			MAX-ACCESS	read-only
			STATUS	current
			::= { hmWanMbus7A 49 }

hmWanMbus7AVIF16		OBJECT-TYPE
			SYNTAX	INTEGER
			MAX-ACCESS	read-only
			STATUS	current
			::= { hmWanMbus7A 50 }

hmWanMbus7AValue16		OBJECT-TYPE
			SYNTAX	INTEGER
			MAX-ACCESS	read-only
			STATUS	current
			::= { hmWanMbus7A 51 }

hmWanMbus7AVIF17		OBJECT-TYPE
			SYNTAX	INTEGER
			MAX-ACCESS	read-only
			STATUS	current
			::= { hmWanMbus7A 52 }

hmWanMbus7AValue17		OBJECT-TYPE
			SYNTAX	INTEGER
			MAX-ACCESS	read-only
			STATUS	current
			::= { hmWanMbus7A 53 }

hmWanMbus7AVIF18		OBJECT-TYPE
			SYNTAX	INTEGER
			MAX-ACCESS	read-only
			STATUS	current
			::= { hmWanMbus7A 54 }

hmWanMbus7AValue18		OBJECT-TYPE
			SYNTAX	INTEGER
			MAX-ACCESS	read-only
			STATUS	current
			::= { hmWanMbus7A 55 }

hmWanMbus7AVIF19		OBJECT-TYPE
			SYNTAX	INTEGER
			MAX-ACCESS	read-only
			STATUS	current
			::= { hmWanMbus7A 56 }

hmWanMbus7AValue19		OBJECT-TYPE
			SYNTAX	INTEGER
			MAX-ACCESS	read-only
			STATUS	current
			::= { hmWanMbus7A 57 }

hmWanMbus7AVIF1A		OBJECT-TYPE
			SYNTAX	INTEGER
			MAX-ACCESS	read-only
			STATUS	current
			::= { hmWanMbus7A 58 }

hmWanMbus7AValue1A		OBJECT-TYPE
			SYNTAX	INTEGER
			MAX-ACCESS	read-only
			STATUS	current
			::= { hmWanMbus7A 59 }

hmWanMbus7AVIF1B		OBJECT-TYPE
			SYNTAX	INTEGER
			MAX-ACCESS	read-only
			STATUS	current
			::= { hmWanMbus7A 60 }

hmWanMbus7AValue1B		OBJECT-TYPE
			SYNTAX	INTEGER
			MAX-ACCESS	read-only
			STATUS	current
			::= { hmWanMbus7A 61 }

hmWanMbus7AVIF1C		OBJECT-TYPE
			SYNTAX	INTEGER
			MAX-ACCESS	read-only
			STATUS	current
			::= { hmWanMbus7A 62 }

hmWanMbus7AValue1C		OBJECT-TYPE
			SYNTAX	INTEGER
			MAX-ACCESS	read-only
			STATUS	current
			::= { hmWanMbus7A 63 }

hmWanMbus7AVIF1D		OBJECT-TYPE
			SYNTAX	INTEGER
			MAX-ACCESS	read-only
			STATUS	current
			::= { hmWanMbus7A 64 }

hmWanMbus7AValue1D		OBJECT-TYPE
			SYNTAX	INTEGER
			MAX-ACCESS	read-only
			STATUS	current
			::= { hmWanMbus7A 65 }

hmWanMbus7AVIF1E		OBJECT-TYPE
			SYNTAX	INTEGER
			MAX-ACCESS	read-only
			STATUS	current
			::= { hmWanMbus7A 66 }

hmWanMbus7AValue1E		OBJECT-TYPE
			SYNTAX	INTEGER
			MAX-ACCESS	read-only
			STATUS	current
			::= { hmWanMbus7A 67 }

hmWanMbus7AVIF1F		OBJECT-TYPE
			SYNTAX	INTEGER
			MAX-ACCESS	read-only
			STATUS	current
			::= { hmWanMbus7A 68 }

hmWanMbus7AValue1F		OBJECT-TYPE
			SYNTAX	INTEGER
			MAX-ACCESS	read-only
			STATUS	current
			::= { hmWanMbus7A 69 }

hmWanMbus7AVIF20		OBJECT-TYPE
			SYNTAX	INTEGER
			MAX-ACCESS	read-only
			STATUS	current
			::= { hmWanMbus7A 70 }

hmWanMbus7AValue20		OBJECT-TYPE
			SYNTAX	INTEGER
			MAX-ACCESS	read-only
			STATUS	current
			::= { hmWanMbus7A 71 }

hmWanMbus7AVIF21		OBJECT-TYPE
			SYNTAX	INTEGER
			MAX-ACCESS	read-only
			STATUS	current
			::= { hmWanMbus7A 72 }

hmWanMbus7AValue21		OBJECT-TYPE
			SYNTAX	INTEGER
			MAX-ACCESS	read-only
			STATUS	current
			::= { hmWanMbus7A 73 }

hmWanMbus7AVIF22		OBJECT-TYPE
			SYNTAX	INTEGER
			MAX-ACCESS	read-only
			STATUS	current
			::= { hmWanMbus7A 74 }

hmWanMbus7AValue22		OBJECT-TYPE
			SYNTAX	INTEGER
			MAX-ACCESS	read-only
			STATUS	current
			::= { hmWanMbus7A 75 }

hmWanMbus7AVIF23		OBJECT-TYPE
			SYNTAX	INTEGER
			MAX-ACCESS	read-only
			STATUS	current
			::= { hmWanMbus7A 76 }

hmWanMbus7AValue23		OBJECT-TYPE
			SYNTAX	INTEGER
			MAX-ACCESS	read-only
			STATUS	current
			::= { hmWanMbus7A 77 }

hmWanMbus7AVIF24		OBJECT-TYPE
			SYNTAX	INTEGER
			MAX-ACCESS	read-only
			STATUS	current
			::= { hmWanMbus7A 78 }

hmWanMbus7AValue24		OBJECT-TYPE
			SYNTAX	INTEGER
			MAX-ACCESS	read-only
			STATUS	current
			::= { hmWanMbus7A 79 }

hmWanMbus7AVIF25		OBJECT-TYPE
			SYNTAX	INTEGER
			MAX-ACCESS	read-only
			STATUS	current
			::= { hmWanMbus7A 80 }

hmWanMbus7AValue25		OBJECT-TYPE
			SYNTAX	INTEGER
			MAX-ACCESS	read-only
			STATUS	current
			::= { hmWanMbus7A 81 }

hmWanMbus7AVIF26		OBJECT-TYPE
			SYNTAX	INTEGER
			MAX-ACCESS	read-only
			STATUS	current
			::= { hmWanMbus7A 82 }

hmWanMbus7AValue26		OBJECT-TYPE
			SYNTAX	INTEGER
			MAX-ACCESS	read-only
			STATUS	current
			::= { hmWanMbus7A 83 }

hmWanMbus7AVIF27		OBJECT-TYPE
			SYNTAX	INTEGER
			MAX-ACCESS	read-only
			STATUS	current
			::= { hmWanMbus7A 84 }

hmWanMbus7AValue27		OBJECT-TYPE
			SYNTAX	INTEGER
			MAX-ACCESS	read-only
			STATUS	current
			::= { hmWanMbus7A 85 }

hmWanMbus7AVIF28		OBJECT-TYPE
			SYNTAX	INTEGER
			MAX-ACCESS	read-only
			STATUS	current
			::= { hmWanMbus7A 86 }

hmWanMbus7AValue28		OBJECT-TYPE
			SYNTAX	INTEGER
			MAX-ACCESS	read-only
			STATUS	current
			::= { hmWanMbus7A 87 }

hmWanMbus7AVIF29		OBJECT-TYPE
			SYNTAX	INTEGER
			MAX-ACCESS	read-only
			STATUS	current
			::= { hmWanMbus7A 88 }

hmWanMbus7AValue29		OBJECT-TYPE
			SYNTAX	INTEGER
			MAX-ACCESS	read-only
			STATUS	current
			::= { hmWanMbus7A 89 }

hmWanMbus7AVIF2A		OBJECT-TYPE
			SYNTAX	INTEGER
			MAX-ACCESS	read-only
			STATUS	current
			::= { hmWanMbus7A 90 }

hmWanMbus7AValue2A		OBJECT-TYPE
			SYNTAX	INTEGER
			MAX-ACCESS	read-only
			STATUS	current
			::= { hmWanMbus7A 91 }

hmWanMbus7AVIF2B		OBJECT-TYPE
			SYNTAX	INTEGER
			MAX-ACCESS	read-only
			STATUS	current
			::= { hmWanMbus7A 92 }

hmWanMbus7AValue2B		OBJECT-TYPE
			SYNTAX	INTEGER
			MAX-ACCESS	read-only
			STATUS	current
			::= { hmWanMbus7A 93 }

hmWanMbus7AVIF2C		OBJECT-TYPE
			SYNTAX	INTEGER
			MAX-ACCESS	read-only
			STATUS	current
			::= { hmWanMbus7A 94 }

hmWanMbus7AValue2C		OBJECT-TYPE
			SYNTAX	INTEGER
			MAX-ACCESS	read-only
			STATUS	current
			::= { hmWanMbus7A 95 }

hmWanMbus7AVIF2D		OBJECT-TYPE
			SYNTAX	INTEGER
			MAX-ACCESS	read-only
			STATUS	current
			::= { hmWanMbus7A 96 }

hmWanMbus7AValue2D		OBJECT-TYPE
			SYNTAX	INTEGER
			MAX-ACCESS	read-only
			STATUS	current
			::= { hmWanMbus7A 97 }

hmWanMbus7AVIF2E		OBJECT-TYPE
			SYNTAX	INTEGER
			MAX-ACCESS	read-only
			STATUS	current
			::= { hmWanMbus7A 98 }

hmWanMbus7AValue2E		OBJECT-TYPE
			SYNTAX	INTEGER
			MAX-ACCESS	read-only
			STATUS	current
			::= { hmWanMbus7A 99 }

hmWanMbus7AVIF2F		OBJECT-TYPE
			SYNTAX	INTEGER
			MAX-ACCESS	read-only
			STATUS	current
			::= { hmWanMbus7A 100 }

hmWanMbus7AValue2F		OBJECT-TYPE
			SYNTAX	INTEGER
			MAX-ACCESS	read-only
			STATUS	current
			::= { hmWanMbus7A 101 }

hmWanMbus7B			OBJECT IDENTIFIER ::= { hmWanMbus 123 }

hmWanMbus7BIdNumber		OBJECT-TYPE
			SYNTAX	Gauge32
			MAX-ACCESS	read-only
			STATUS	current
			::= { hmWanMbus7B 1 }

hmWanMbus7BManufacturer	OBJECT-TYPE
			SYNTAX	Gauge32
			MAX-ACCESS	read-only
			STATUS	current
			::= { hmWanMbus7B 2 }

hmWanMbus7BVersion		OBJECT-TYPE
			SYNTAX	Gauge32
			MAX-ACCESS	read-only
			STATUS	current
			::= { hmWanMbus7B 3 }

hmWanMbus7BMedium		OBJECT-TYPE
			SYNTAX	Gauge32
			MAX-ACCESS	read-only
			STATUS	current
			::= { hmWanMbus7B 4 }

hmWanMbus7BStatus		OBJECT-TYPE
			SYNTAX	Gauge32
			MAX-ACCESS	read-only
			STATUS	current
			::= { hmWanMbus7B 5 }

hmWanMbus7BVIF00		OBJECT-TYPE
			SYNTAX	INTEGER
			MAX-ACCESS	read-only
			STATUS	current
			::= { hmWanMbus7B 6 }

hmWanMbus7BValue00		OBJECT-TYPE
			SYNTAX	INTEGER
			MAX-ACCESS	read-only
			STATUS	current
			::= { hmWanMbus7B 7 }

hmWanMbus7BVIF01		OBJECT-TYPE
			SYNTAX	INTEGER
			MAX-ACCESS	read-only
			STATUS	current
			::= { hmWanMbus7B 8 }

hmWanMbus7BValue01		OBJECT-TYPE
			SYNTAX	INTEGER
			MAX-ACCESS	read-only
			STATUS	current
			::= { hmWanMbus7B 9 }

hmWanMbus7BVIF02		OBJECT-TYPE
			SYNTAX	INTEGER
			MAX-ACCESS	read-only
			STATUS	current
			::= { hmWanMbus7B 10 }

hmWanMbus7BValue02		OBJECT-TYPE
			SYNTAX	INTEGER
			MAX-ACCESS	read-only
			STATUS	current
			::= { hmWanMbus7B 11 }

hmWanMbus7BVIF03		OBJECT-TYPE
			SYNTAX	INTEGER
			MAX-ACCESS	read-only
			STATUS	current
			::= { hmWanMbus7B 12 }

hmWanMbus7BValue03		OBJECT-TYPE
			SYNTAX	INTEGER
			MAX-ACCESS	read-only
			STATUS	current
			::= { hmWanMbus7B 13 }

hmWanMbus7BVIF04		OBJECT-TYPE
			SYNTAX	INTEGER
			MAX-ACCESS	read-only
			STATUS	current
			::= { hmWanMbus7B 14 }

hmWanMbus7BValue04		OBJECT-TYPE
			SYNTAX	INTEGER
			MAX-ACCESS	read-only
			STATUS	current
			::= { hmWanMbus7B 15 }

hmWanMbus7BVIF05		OBJECT-TYPE
			SYNTAX	INTEGER
			MAX-ACCESS	read-only
			STATUS	current
			::= { hmWanMbus7B 16 }

hmWanMbus7BValue05		OBJECT-TYPE
			SYNTAX	INTEGER
			MAX-ACCESS	read-only
			STATUS	current
			::= { hmWanMbus7B 17 }

hmWanMbus7BVIF06		OBJECT-TYPE
			SYNTAX	INTEGER
			MAX-ACCESS	read-only
			STATUS	current
			::= { hmWanMbus7B 18 }

hmWanMbus7BValue06		OBJECT-TYPE
			SYNTAX	INTEGER
			MAX-ACCESS	read-only
			STATUS	current
			::= { hmWanMbus7B 19 }

hmWanMbus7BVIF07		OBJECT-TYPE
			SYNTAX	INTEGER
			MAX-ACCESS	read-only
			STATUS	current
			::= { hmWanMbus7B 20 }

hmWanMbus7BValue07		OBJECT-TYPE
			SYNTAX	INTEGER
			MAX-ACCESS	read-only
			STATUS	current
			::= { hmWanMbus7B 21 }

hmWanMbus7BVIF08		OBJECT-TYPE
			SYNTAX	INTEGER
			MAX-ACCESS	read-only
			STATUS	current
			::= { hmWanMbus7B 22 }

hmWanMbus7BValue08		OBJECT-TYPE
			SYNTAX	INTEGER
			MAX-ACCESS	read-only
			STATUS	current
			::= { hmWanMbus7B 23 }

hmWanMbus7BVIF09		OBJECT-TYPE
			SYNTAX	INTEGER
			MAX-ACCESS	read-only
			STATUS	current
			::= { hmWanMbus7B 24 }

hmWanMbus7BValue09		OBJECT-TYPE
			SYNTAX	INTEGER
			MAX-ACCESS	read-only
			STATUS	current
			::= { hmWanMbus7B 25 }

hmWanMbus7BVIF0A		OBJECT-TYPE
			SYNTAX	INTEGER
			MAX-ACCESS	read-only
			STATUS	current
			::= { hmWanMbus7B 26 }

hmWanMbus7BValue0A		OBJECT-TYPE
			SYNTAX	INTEGER
			MAX-ACCESS	read-only
			STATUS	current
			::= { hmWanMbus7B 27 }

hmWanMbus7BVIF0B		OBJECT-TYPE
			SYNTAX	INTEGER
			MAX-ACCESS	read-only
			STATUS	current
			::= { hmWanMbus7B 28 }

hmWanMbus7BValue0B		OBJECT-TYPE
			SYNTAX	INTEGER
			MAX-ACCESS	read-only
			STATUS	current
			::= { hmWanMbus7B 29 }

hmWanMbus7BVIF0C		OBJECT-TYPE
			SYNTAX	INTEGER
			MAX-ACCESS	read-only
			STATUS	current
			::= { hmWanMbus7B 30 }

hmWanMbus7BValue0C		OBJECT-TYPE
			SYNTAX	INTEGER
			MAX-ACCESS	read-only
			STATUS	current
			::= { hmWanMbus7B 31 }

hmWanMbus7BVIF0D		OBJECT-TYPE
			SYNTAX	INTEGER
			MAX-ACCESS	read-only
			STATUS	current
			::= { hmWanMbus7B 32 }

hmWanMbus7BValue0D		OBJECT-TYPE
			SYNTAX	INTEGER
			MAX-ACCESS	read-only
			STATUS	current
			::= { hmWanMbus7B 33 }

hmWanMbus7BVIF0E		OBJECT-TYPE
			SYNTAX	INTEGER
			MAX-ACCESS	read-only
			STATUS	current
			::= { hmWanMbus7B 34 }

hmWanMbus7BValue0E		OBJECT-TYPE
			SYNTAX	INTEGER
			MAX-ACCESS	read-only
			STATUS	current
			::= { hmWanMbus7B 35 }

hmWanMbus7BVIF0F		OBJECT-TYPE
			SYNTAX	INTEGER
			MAX-ACCESS	read-only
			STATUS	current
			::= { hmWanMbus7B 36 }

hmWanMbus7BValue0F		OBJECT-TYPE
			SYNTAX	INTEGER
			MAX-ACCESS	read-only
			STATUS	current
			::= { hmWanMbus7B 37 }

hmWanMbus7BVIF10		OBJECT-TYPE
			SYNTAX	INTEGER
			MAX-ACCESS	read-only
			STATUS	current
			::= { hmWanMbus7B 38 }

hmWanMbus7BValue10		OBJECT-TYPE
			SYNTAX	INTEGER
			MAX-ACCESS	read-only
			STATUS	current
			::= { hmWanMbus7B 39 }

hmWanMbus7BVIF11		OBJECT-TYPE
			SYNTAX	INTEGER
			MAX-ACCESS	read-only
			STATUS	current
			::= { hmWanMbus7B 40 }

hmWanMbus7BValue11		OBJECT-TYPE
			SYNTAX	INTEGER
			MAX-ACCESS	read-only
			STATUS	current
			::= { hmWanMbus7B 41 }

hmWanMbus7BVIF12		OBJECT-TYPE
			SYNTAX	INTEGER
			MAX-ACCESS	read-only
			STATUS	current
			::= { hmWanMbus7B 42 }

hmWanMbus7BValue12		OBJECT-TYPE
			SYNTAX	INTEGER
			MAX-ACCESS	read-only
			STATUS	current
			::= { hmWanMbus7B 43 }

hmWanMbus7BVIF13		OBJECT-TYPE
			SYNTAX	INTEGER
			MAX-ACCESS	read-only
			STATUS	current
			::= { hmWanMbus7B 44 }

hmWanMbus7BValue13		OBJECT-TYPE
			SYNTAX	INTEGER
			MAX-ACCESS	read-only
			STATUS	current
			::= { hmWanMbus7B 45 }

hmWanMbus7BVIF14		OBJECT-TYPE
			SYNTAX	INTEGER
			MAX-ACCESS	read-only
			STATUS	current
			::= { hmWanMbus7B 46 }

hmWanMbus7BValue14		OBJECT-TYPE
			SYNTAX	INTEGER
			MAX-ACCESS	read-only
			STATUS	current
			::= { hmWanMbus7B 47 }

hmWanMbus7BVIF15		OBJECT-TYPE
			SYNTAX	INTEGER
			MAX-ACCESS	read-only
			STATUS	current
			::= { hmWanMbus7B 48 }

hmWanMbus7BValue15		OBJECT-TYPE
			SYNTAX	INTEGER
			MAX-ACCESS	read-only
			STATUS	current
			::= { hmWanMbus7B 49 }

hmWanMbus7BVIF16		OBJECT-TYPE
			SYNTAX	INTEGER
			MAX-ACCESS	read-only
			STATUS	current
			::= { hmWanMbus7B 50 }

hmWanMbus7BValue16		OBJECT-TYPE
			SYNTAX	INTEGER
			MAX-ACCESS	read-only
			STATUS	current
			::= { hmWanMbus7B 51 }

hmWanMbus7BVIF17		OBJECT-TYPE
			SYNTAX	INTEGER
			MAX-ACCESS	read-only
			STATUS	current
			::= { hmWanMbus7B 52 }

hmWanMbus7BValue17		OBJECT-TYPE
			SYNTAX	INTEGER
			MAX-ACCESS	read-only
			STATUS	current
			::= { hmWanMbus7B 53 }

hmWanMbus7BVIF18		OBJECT-TYPE
			SYNTAX	INTEGER
			MAX-ACCESS	read-only
			STATUS	current
			::= { hmWanMbus7B 54 }

hmWanMbus7BValue18		OBJECT-TYPE
			SYNTAX	INTEGER
			MAX-ACCESS	read-only
			STATUS	current
			::= { hmWanMbus7B 55 }

hmWanMbus7BVIF19		OBJECT-TYPE
			SYNTAX	INTEGER
			MAX-ACCESS	read-only
			STATUS	current
			::= { hmWanMbus7B 56 }

hmWanMbus7BValue19		OBJECT-TYPE
			SYNTAX	INTEGER
			MAX-ACCESS	read-only
			STATUS	current
			::= { hmWanMbus7B 57 }

hmWanMbus7BVIF1A		OBJECT-TYPE
			SYNTAX	INTEGER
			MAX-ACCESS	read-only
			STATUS	current
			::= { hmWanMbus7B 58 }

hmWanMbus7BValue1A		OBJECT-TYPE
			SYNTAX	INTEGER
			MAX-ACCESS	read-only
			STATUS	current
			::= { hmWanMbus7B 59 }

hmWanMbus7BVIF1B		OBJECT-TYPE
			SYNTAX	INTEGER
			MAX-ACCESS	read-only
			STATUS	current
			::= { hmWanMbus7B 60 }

hmWanMbus7BValue1B		OBJECT-TYPE
			SYNTAX	INTEGER
			MAX-ACCESS	read-only
			STATUS	current
			::= { hmWanMbus7B 61 }

hmWanMbus7BVIF1C		OBJECT-TYPE
			SYNTAX	INTEGER
			MAX-ACCESS	read-only
			STATUS	current
			::= { hmWanMbus7B 62 }

hmWanMbus7BValue1C		OBJECT-TYPE
			SYNTAX	INTEGER
			MAX-ACCESS	read-only
			STATUS	current
			::= { hmWanMbus7B 63 }

hmWanMbus7BVIF1D		OBJECT-TYPE
			SYNTAX	INTEGER
			MAX-ACCESS	read-only
			STATUS	current
			::= { hmWanMbus7B 64 }

hmWanMbus7BValue1D		OBJECT-TYPE
			SYNTAX	INTEGER
			MAX-ACCESS	read-only
			STATUS	current
			::= { hmWanMbus7B 65 }

hmWanMbus7BVIF1E		OBJECT-TYPE
			SYNTAX	INTEGER
			MAX-ACCESS	read-only
			STATUS	current
			::= { hmWanMbus7B 66 }

hmWanMbus7BValue1E		OBJECT-TYPE
			SYNTAX	INTEGER
			MAX-ACCESS	read-only
			STATUS	current
			::= { hmWanMbus7B 67 }

hmWanMbus7BVIF1F		OBJECT-TYPE
			SYNTAX	INTEGER
			MAX-ACCESS	read-only
			STATUS	current
			::= { hmWanMbus7B 68 }

hmWanMbus7BValue1F		OBJECT-TYPE
			SYNTAX	INTEGER
			MAX-ACCESS	read-only
			STATUS	current
			::= { hmWanMbus7B 69 }

hmWanMbus7BVIF20		OBJECT-TYPE
			SYNTAX	INTEGER
			MAX-ACCESS	read-only
			STATUS	current
			::= { hmWanMbus7B 70 }

hmWanMbus7BValue20		OBJECT-TYPE
			SYNTAX	INTEGER
			MAX-ACCESS	read-only
			STATUS	current
			::= { hmWanMbus7B 71 }

hmWanMbus7BVIF21		OBJECT-TYPE
			SYNTAX	INTEGER
			MAX-ACCESS	read-only
			STATUS	current
			::= { hmWanMbus7B 72 }

hmWanMbus7BValue21		OBJECT-TYPE
			SYNTAX	INTEGER
			MAX-ACCESS	read-only
			STATUS	current
			::= { hmWanMbus7B 73 }

hmWanMbus7BVIF22		OBJECT-TYPE
			SYNTAX	INTEGER
			MAX-ACCESS	read-only
			STATUS	current
			::= { hmWanMbus7B 74 }

hmWanMbus7BValue22		OBJECT-TYPE
			SYNTAX	INTEGER
			MAX-ACCESS	read-only
			STATUS	current
			::= { hmWanMbus7B 75 }

hmWanMbus7BVIF23		OBJECT-TYPE
			SYNTAX	INTEGER
			MAX-ACCESS	read-only
			STATUS	current
			::= { hmWanMbus7B 76 }

hmWanMbus7BValue23		OBJECT-TYPE
			SYNTAX	INTEGER
			MAX-ACCESS	read-only
			STATUS	current
			::= { hmWanMbus7B 77 }

hmWanMbus7BVIF24		OBJECT-TYPE
			SYNTAX	INTEGER
			MAX-ACCESS	read-only
			STATUS	current
			::= { hmWanMbus7B 78 }

hmWanMbus7BValue24		OBJECT-TYPE
			SYNTAX	INTEGER
			MAX-ACCESS	read-only
			STATUS	current
			::= { hmWanMbus7B 79 }

hmWanMbus7BVIF25		OBJECT-TYPE
			SYNTAX	INTEGER
			MAX-ACCESS	read-only
			STATUS	current
			::= { hmWanMbus7B 80 }

hmWanMbus7BValue25		OBJECT-TYPE
			SYNTAX	INTEGER
			MAX-ACCESS	read-only
			STATUS	current
			::= { hmWanMbus7B 81 }

hmWanMbus7BVIF26		OBJECT-TYPE
			SYNTAX	INTEGER
			MAX-ACCESS	read-only
			STATUS	current
			::= { hmWanMbus7B 82 }

hmWanMbus7BValue26		OBJECT-TYPE
			SYNTAX	INTEGER
			MAX-ACCESS	read-only
			STATUS	current
			::= { hmWanMbus7B 83 }

hmWanMbus7BVIF27		OBJECT-TYPE
			SYNTAX	INTEGER
			MAX-ACCESS	read-only
			STATUS	current
			::= { hmWanMbus7B 84 }

hmWanMbus7BValue27		OBJECT-TYPE
			SYNTAX	INTEGER
			MAX-ACCESS	read-only
			STATUS	current
			::= { hmWanMbus7B 85 }

hmWanMbus7BVIF28		OBJECT-TYPE
			SYNTAX	INTEGER
			MAX-ACCESS	read-only
			STATUS	current
			::= { hmWanMbus7B 86 }

hmWanMbus7BValue28		OBJECT-TYPE
			SYNTAX	INTEGER
			MAX-ACCESS	read-only
			STATUS	current
			::= { hmWanMbus7B 87 }

hmWanMbus7BVIF29		OBJECT-TYPE
			SYNTAX	INTEGER
			MAX-ACCESS	read-only
			STATUS	current
			::= { hmWanMbus7B 88 }

hmWanMbus7BValue29		OBJECT-TYPE
			SYNTAX	INTEGER
			MAX-ACCESS	read-only
			STATUS	current
			::= { hmWanMbus7B 89 }

hmWanMbus7BVIF2A		OBJECT-TYPE
			SYNTAX	INTEGER
			MAX-ACCESS	read-only
			STATUS	current
			::= { hmWanMbus7B 90 }

hmWanMbus7BValue2A		OBJECT-TYPE
			SYNTAX	INTEGER
			MAX-ACCESS	read-only
			STATUS	current
			::= { hmWanMbus7B 91 }

hmWanMbus7BVIF2B		OBJECT-TYPE
			SYNTAX	INTEGER
			MAX-ACCESS	read-only
			STATUS	current
			::= { hmWanMbus7B 92 }

hmWanMbus7BValue2B		OBJECT-TYPE
			SYNTAX	INTEGER
			MAX-ACCESS	read-only
			STATUS	current
			::= { hmWanMbus7B 93 }

hmWanMbus7BVIF2C		OBJECT-TYPE
			SYNTAX	INTEGER
			MAX-ACCESS	read-only
			STATUS	current
			::= { hmWanMbus7B 94 }

hmWanMbus7BValue2C		OBJECT-TYPE
			SYNTAX	INTEGER
			MAX-ACCESS	read-only
			STATUS	current
			::= { hmWanMbus7B 95 }

hmWanMbus7BVIF2D		OBJECT-TYPE
			SYNTAX	INTEGER
			MAX-ACCESS	read-only
			STATUS	current
			::= { hmWanMbus7B 96 }

hmWanMbus7BValue2D		OBJECT-TYPE
			SYNTAX	INTEGER
			MAX-ACCESS	read-only
			STATUS	current
			::= { hmWanMbus7B 97 }

hmWanMbus7BVIF2E		OBJECT-TYPE
			SYNTAX	INTEGER
			MAX-ACCESS	read-only
			STATUS	current
			::= { hmWanMbus7B 98 }

hmWanMbus7BValue2E		OBJECT-TYPE
			SYNTAX	INTEGER
			MAX-ACCESS	read-only
			STATUS	current
			::= { hmWanMbus7B 99 }

hmWanMbus7BVIF2F		OBJECT-TYPE
			SYNTAX	INTEGER
			MAX-ACCESS	read-only
			STATUS	current
			::= { hmWanMbus7B 100 }

hmWanMbus7BValue2F		OBJECT-TYPE
			SYNTAX	INTEGER
			MAX-ACCESS	read-only
			STATUS	current
			::= { hmWanMbus7B 101 }

hmWanMbus7C			OBJECT IDENTIFIER ::= { hmWanMbus 124 }

hmWanMbus7CIdNumber		OBJECT-TYPE
			SYNTAX	Gauge32
			MAX-ACCESS	read-only
			STATUS	current
			::= { hmWanMbus7C 1 }

hmWanMbus7CManufacturer	OBJECT-TYPE
			SYNTAX	Gauge32
			MAX-ACCESS	read-only
			STATUS	current
			::= { hmWanMbus7C 2 }

hmWanMbus7CVersion		OBJECT-TYPE
			SYNTAX	Gauge32
			MAX-ACCESS	read-only
			STATUS	current
			::= { hmWanMbus7C 3 }

hmWanMbus7CMedium		OBJECT-TYPE
			SYNTAX	Gauge32
			MAX-ACCESS	read-only
			STATUS	current
			::= { hmWanMbus7C 4 }

hmWanMbus7CStatus		OBJECT-TYPE
			SYNTAX	Gauge32
			MAX-ACCESS	read-only
			STATUS	current
			::= { hmWanMbus7C 5 }

hmWanMbus7CVIF00		OBJECT-TYPE
			SYNTAX	INTEGER
			MAX-ACCESS	read-only
			STATUS	current
			::= { hmWanMbus7C 6 }

hmWanMbus7CValue00		OBJECT-TYPE
			SYNTAX	INTEGER
			MAX-ACCESS	read-only
			STATUS	current
			::= { hmWanMbus7C 7 }

hmWanMbus7CVIF01		OBJECT-TYPE
			SYNTAX	INTEGER
			MAX-ACCESS	read-only
			STATUS	current
			::= { hmWanMbus7C 8 }

hmWanMbus7CValue01		OBJECT-TYPE
			SYNTAX	INTEGER
			MAX-ACCESS	read-only
			STATUS	current
			::= { hmWanMbus7C 9 }

hmWanMbus7CVIF02		OBJECT-TYPE
			SYNTAX	INTEGER
			MAX-ACCESS	read-only
			STATUS	current
			::= { hmWanMbus7C 10 }

hmWanMbus7CValue02		OBJECT-TYPE
			SYNTAX	INTEGER
			MAX-ACCESS	read-only
			STATUS	current
			::= { hmWanMbus7C 11 }

hmWanMbus7CVIF03		OBJECT-TYPE
			SYNTAX	INTEGER
			MAX-ACCESS	read-only
			STATUS	current
			::= { hmWanMbus7C 12 }

hmWanMbus7CValue03		OBJECT-TYPE
			SYNTAX	INTEGER
			MAX-ACCESS	read-only
			STATUS	current
			::= { hmWanMbus7C 13 }

hmWanMbus7CVIF04		OBJECT-TYPE
			SYNTAX	INTEGER
			MAX-ACCESS	read-only
			STATUS	current
			::= { hmWanMbus7C 14 }

hmWanMbus7CValue04		OBJECT-TYPE
			SYNTAX	INTEGER
			MAX-ACCESS	read-only
			STATUS	current
			::= { hmWanMbus7C 15 }

hmWanMbus7CVIF05		OBJECT-TYPE
			SYNTAX	INTEGER
			MAX-ACCESS	read-only
			STATUS	current
			::= { hmWanMbus7C 16 }

hmWanMbus7CValue05		OBJECT-TYPE
			SYNTAX	INTEGER
			MAX-ACCESS	read-only
			STATUS	current
			::= { hmWanMbus7C 17 }

hmWanMbus7CVIF06		OBJECT-TYPE
			SYNTAX	INTEGER
			MAX-ACCESS	read-only
			STATUS	current
			::= { hmWanMbus7C 18 }

hmWanMbus7CValue06		OBJECT-TYPE
			SYNTAX	INTEGER
			MAX-ACCESS	read-only
			STATUS	current
			::= { hmWanMbus7C 19 }

hmWanMbus7CVIF07		OBJECT-TYPE
			SYNTAX	INTEGER
			MAX-ACCESS	read-only
			STATUS	current
			::= { hmWanMbus7C 20 }

hmWanMbus7CValue07		OBJECT-TYPE
			SYNTAX	INTEGER
			MAX-ACCESS	read-only
			STATUS	current
			::= { hmWanMbus7C 21 }

hmWanMbus7CVIF08		OBJECT-TYPE
			SYNTAX	INTEGER
			MAX-ACCESS	read-only
			STATUS	current
			::= { hmWanMbus7C 22 }

hmWanMbus7CValue08		OBJECT-TYPE
			SYNTAX	INTEGER
			MAX-ACCESS	read-only
			STATUS	current
			::= { hmWanMbus7C 23 }

hmWanMbus7CVIF09		OBJECT-TYPE
			SYNTAX	INTEGER
			MAX-ACCESS	read-only
			STATUS	current
			::= { hmWanMbus7C 24 }

hmWanMbus7CValue09		OBJECT-TYPE
			SYNTAX	INTEGER
			MAX-ACCESS	read-only
			STATUS	current
			::= { hmWanMbus7C 25 }

hmWanMbus7CVIF0A		OBJECT-TYPE
			SYNTAX	INTEGER
			MAX-ACCESS	read-only
			STATUS	current
			::= { hmWanMbus7C 26 }

hmWanMbus7CValue0A		OBJECT-TYPE
			SYNTAX	INTEGER
			MAX-ACCESS	read-only
			STATUS	current
			::= { hmWanMbus7C 27 }

hmWanMbus7CVIF0B		OBJECT-TYPE
			SYNTAX	INTEGER
			MAX-ACCESS	read-only
			STATUS	current
			::= { hmWanMbus7C 28 }

hmWanMbus7CValue0B		OBJECT-TYPE
			SYNTAX	INTEGER
			MAX-ACCESS	read-only
			STATUS	current
			::= { hmWanMbus7C 29 }

hmWanMbus7CVIF0C		OBJECT-TYPE
			SYNTAX	INTEGER
			MAX-ACCESS	read-only
			STATUS	current
			::= { hmWanMbus7C 30 }

hmWanMbus7CValue0C		OBJECT-TYPE
			SYNTAX	INTEGER
			MAX-ACCESS	read-only
			STATUS	current
			::= { hmWanMbus7C 31 }

hmWanMbus7CVIF0D		OBJECT-TYPE
			SYNTAX	INTEGER
			MAX-ACCESS	read-only
			STATUS	current
			::= { hmWanMbus7C 32 }

hmWanMbus7CValue0D		OBJECT-TYPE
			SYNTAX	INTEGER
			MAX-ACCESS	read-only
			STATUS	current
			::= { hmWanMbus7C 33 }

hmWanMbus7CVIF0E		OBJECT-TYPE
			SYNTAX	INTEGER
			MAX-ACCESS	read-only
			STATUS	current
			::= { hmWanMbus7C 34 }

hmWanMbus7CValue0E		OBJECT-TYPE
			SYNTAX	INTEGER
			MAX-ACCESS	read-only
			STATUS	current
			::= { hmWanMbus7C 35 }

hmWanMbus7CVIF0F		OBJECT-TYPE
			SYNTAX	INTEGER
			MAX-ACCESS	read-only
			STATUS	current
			::= { hmWanMbus7C 36 }

hmWanMbus7CValue0F		OBJECT-TYPE
			SYNTAX	INTEGER
			MAX-ACCESS	read-only
			STATUS	current
			::= { hmWanMbus7C 37 }

hmWanMbus7CVIF10		OBJECT-TYPE
			SYNTAX	INTEGER
			MAX-ACCESS	read-only
			STATUS	current
			::= { hmWanMbus7C 38 }

hmWanMbus7CValue10		OBJECT-TYPE
			SYNTAX	INTEGER
			MAX-ACCESS	read-only
			STATUS	current
			::= { hmWanMbus7C 39 }

hmWanMbus7CVIF11		OBJECT-TYPE
			SYNTAX	INTEGER
			MAX-ACCESS	read-only
			STATUS	current
			::= { hmWanMbus7C 40 }

hmWanMbus7CValue11		OBJECT-TYPE
			SYNTAX	INTEGER
			MAX-ACCESS	read-only
			STATUS	current
			::= { hmWanMbus7C 41 }

hmWanMbus7CVIF12		OBJECT-TYPE
			SYNTAX	INTEGER
			MAX-ACCESS	read-only
			STATUS	current
			::= { hmWanMbus7C 42 }

hmWanMbus7CValue12		OBJECT-TYPE
			SYNTAX	INTEGER
			MAX-ACCESS	read-only
			STATUS	current
			::= { hmWanMbus7C 43 }

hmWanMbus7CVIF13		OBJECT-TYPE
			SYNTAX	INTEGER
			MAX-ACCESS	read-only
			STATUS	current
			::= { hmWanMbus7C 44 }

hmWanMbus7CValue13		OBJECT-TYPE
			SYNTAX	INTEGER
			MAX-ACCESS	read-only
			STATUS	current
			::= { hmWanMbus7C 45 }

hmWanMbus7CVIF14		OBJECT-TYPE
			SYNTAX	INTEGER
			MAX-ACCESS	read-only
			STATUS	current
			::= { hmWanMbus7C 46 }

hmWanMbus7CValue14		OBJECT-TYPE
			SYNTAX	INTEGER
			MAX-ACCESS	read-only
			STATUS	current
			::= { hmWanMbus7C 47 }

hmWanMbus7CVIF15		OBJECT-TYPE
			SYNTAX	INTEGER
			MAX-ACCESS	read-only
			STATUS	current
			::= { hmWanMbus7C 48 }

hmWanMbus7CValue15		OBJECT-TYPE
			SYNTAX	INTEGER
			MAX-ACCESS	read-only
			STATUS	current
			::= { hmWanMbus7C 49 }

hmWanMbus7CVIF16		OBJECT-TYPE
			SYNTAX	INTEGER
			MAX-ACCESS	read-only
			STATUS	current
			::= { hmWanMbus7C 50 }

hmWanMbus7CValue16		OBJECT-TYPE
			SYNTAX	INTEGER
			MAX-ACCESS	read-only
			STATUS	current
			::= { hmWanMbus7C 51 }

hmWanMbus7CVIF17		OBJECT-TYPE
			SYNTAX	INTEGER
			MAX-ACCESS	read-only
			STATUS	current
			::= { hmWanMbus7C 52 }

hmWanMbus7CValue17		OBJECT-TYPE
			SYNTAX	INTEGER
			MAX-ACCESS	read-only
			STATUS	current
			::= { hmWanMbus7C 53 }

hmWanMbus7CVIF18		OBJECT-TYPE
			SYNTAX	INTEGER
			MAX-ACCESS	read-only
			STATUS	current
			::= { hmWanMbus7C 54 }

hmWanMbus7CValue18		OBJECT-TYPE
			SYNTAX	INTEGER
			MAX-ACCESS	read-only
			STATUS	current
			::= { hmWanMbus7C 55 }

hmWanMbus7CVIF19		OBJECT-TYPE
			SYNTAX	INTEGER
			MAX-ACCESS	read-only
			STATUS	current
			::= { hmWanMbus7C 56 }

hmWanMbus7CValue19		OBJECT-TYPE
			SYNTAX	INTEGER
			MAX-ACCESS	read-only
			STATUS	current
			::= { hmWanMbus7C 57 }

hmWanMbus7CVIF1A		OBJECT-TYPE
			SYNTAX	INTEGER
			MAX-ACCESS	read-only
			STATUS	current
			::= { hmWanMbus7C 58 }

hmWanMbus7CValue1A		OBJECT-TYPE
			SYNTAX	INTEGER
			MAX-ACCESS	read-only
			STATUS	current
			::= { hmWanMbus7C 59 }

hmWanMbus7CVIF1B		OBJECT-TYPE
			SYNTAX	INTEGER
			MAX-ACCESS	read-only
			STATUS	current
			::= { hmWanMbus7C 60 }

hmWanMbus7CValue1B		OBJECT-TYPE
			SYNTAX	INTEGER
			MAX-ACCESS	read-only
			STATUS	current
			::= { hmWanMbus7C 61 }

hmWanMbus7CVIF1C		OBJECT-TYPE
			SYNTAX	INTEGER
			MAX-ACCESS	read-only
			STATUS	current
			::= { hmWanMbus7C 62 }

hmWanMbus7CValue1C		OBJECT-TYPE
			SYNTAX	INTEGER
			MAX-ACCESS	read-only
			STATUS	current
			::= { hmWanMbus7C 63 }

hmWanMbus7CVIF1D		OBJECT-TYPE
			SYNTAX	INTEGER
			MAX-ACCESS	read-only
			STATUS	current
			::= { hmWanMbus7C 64 }

hmWanMbus7CValue1D		OBJECT-TYPE
			SYNTAX	INTEGER
			MAX-ACCESS	read-only
			STATUS	current
			::= { hmWanMbus7C 65 }

hmWanMbus7CVIF1E		OBJECT-TYPE
			SYNTAX	INTEGER
			MAX-ACCESS	read-only
			STATUS	current
			::= { hmWanMbus7C 66 }

hmWanMbus7CValue1E		OBJECT-TYPE
			SYNTAX	INTEGER
			MAX-ACCESS	read-only
			STATUS	current
			::= { hmWanMbus7C 67 }

hmWanMbus7CVIF1F		OBJECT-TYPE
			SYNTAX	INTEGER
			MAX-ACCESS	read-only
			STATUS	current
			::= { hmWanMbus7C 68 }

hmWanMbus7CValue1F		OBJECT-TYPE
			SYNTAX	INTEGER
			MAX-ACCESS	read-only
			STATUS	current
			::= { hmWanMbus7C 69 }

hmWanMbus7CVIF20		OBJECT-TYPE
			SYNTAX	INTEGER
			MAX-ACCESS	read-only
			STATUS	current
			::= { hmWanMbus7C 70 }

hmWanMbus7CValue20		OBJECT-TYPE
			SYNTAX	INTEGER
			MAX-ACCESS	read-only
			STATUS	current
			::= { hmWanMbus7C 71 }

hmWanMbus7CVIF21		OBJECT-TYPE
			SYNTAX	INTEGER
			MAX-ACCESS	read-only
			STATUS	current
			::= { hmWanMbus7C 72 }

hmWanMbus7CValue21		OBJECT-TYPE
			SYNTAX	INTEGER
			MAX-ACCESS	read-only
			STATUS	current
			::= { hmWanMbus7C 73 }

hmWanMbus7CVIF22		OBJECT-TYPE
			SYNTAX	INTEGER
			MAX-ACCESS	read-only
			STATUS	current
			::= { hmWanMbus7C 74 }

hmWanMbus7CValue22		OBJECT-TYPE
			SYNTAX	INTEGER
			MAX-ACCESS	read-only
			STATUS	current
			::= { hmWanMbus7C 75 }

hmWanMbus7CVIF23		OBJECT-TYPE
			SYNTAX	INTEGER
			MAX-ACCESS	read-only
			STATUS	current
			::= { hmWanMbus7C 76 }

hmWanMbus7CValue23		OBJECT-TYPE
			SYNTAX	INTEGER
			MAX-ACCESS	read-only
			STATUS	current
			::= { hmWanMbus7C 77 }

hmWanMbus7CVIF24		OBJECT-TYPE
			SYNTAX	INTEGER
			MAX-ACCESS	read-only
			STATUS	current
			::= { hmWanMbus7C 78 }

hmWanMbus7CValue24		OBJECT-TYPE
			SYNTAX	INTEGER
			MAX-ACCESS	read-only
			STATUS	current
			::= { hmWanMbus7C 79 }

hmWanMbus7CVIF25		OBJECT-TYPE
			SYNTAX	INTEGER
			MAX-ACCESS	read-only
			STATUS	current
			::= { hmWanMbus7C 80 }

hmWanMbus7CValue25		OBJECT-TYPE
			SYNTAX	INTEGER
			MAX-ACCESS	read-only
			STATUS	current
			::= { hmWanMbus7C 81 }

hmWanMbus7CVIF26		OBJECT-TYPE
			SYNTAX	INTEGER
			MAX-ACCESS	read-only
			STATUS	current
			::= { hmWanMbus7C 82 }

hmWanMbus7CValue26		OBJECT-TYPE
			SYNTAX	INTEGER
			MAX-ACCESS	read-only
			STATUS	current
			::= { hmWanMbus7C 83 }

hmWanMbus7CVIF27		OBJECT-TYPE
			SYNTAX	INTEGER
			MAX-ACCESS	read-only
			STATUS	current
			::= { hmWanMbus7C 84 }

hmWanMbus7CValue27		OBJECT-TYPE
			SYNTAX	INTEGER
			MAX-ACCESS	read-only
			STATUS	current
			::= { hmWanMbus7C 85 }

hmWanMbus7CVIF28		OBJECT-TYPE
			SYNTAX	INTEGER
			MAX-ACCESS	read-only
			STATUS	current
			::= { hmWanMbus7C 86 }

hmWanMbus7CValue28		OBJECT-TYPE
			SYNTAX	INTEGER
			MAX-ACCESS	read-only
			STATUS	current
			::= { hmWanMbus7C 87 }

hmWanMbus7CVIF29		OBJECT-TYPE
			SYNTAX	INTEGER
			MAX-ACCESS	read-only
			STATUS	current
			::= { hmWanMbus7C 88 }

hmWanMbus7CValue29		OBJECT-TYPE
			SYNTAX	INTEGER
			MAX-ACCESS	read-only
			STATUS	current
			::= { hmWanMbus7C 89 }

hmWanMbus7CVIF2A		OBJECT-TYPE
			SYNTAX	INTEGER
			MAX-ACCESS	read-only
			STATUS	current
			::= { hmWanMbus7C 90 }

hmWanMbus7CValue2A		OBJECT-TYPE
			SYNTAX	INTEGER
			MAX-ACCESS	read-only
			STATUS	current
			::= { hmWanMbus7C 91 }

hmWanMbus7CVIF2B		OBJECT-TYPE
			SYNTAX	INTEGER
			MAX-ACCESS	read-only
			STATUS	current
			::= { hmWanMbus7C 92 }

hmWanMbus7CValue2B		OBJECT-TYPE
			SYNTAX	INTEGER
			MAX-ACCESS	read-only
			STATUS	current
			::= { hmWanMbus7C 93 }

hmWanMbus7CVIF2C		OBJECT-TYPE
			SYNTAX	INTEGER
			MAX-ACCESS	read-only
			STATUS	current
			::= { hmWanMbus7C 94 }

hmWanMbus7CValue2C		OBJECT-TYPE
			SYNTAX	INTEGER
			MAX-ACCESS	read-only
			STATUS	current
			::= { hmWanMbus7C 95 }

hmWanMbus7CVIF2D		OBJECT-TYPE
			SYNTAX	INTEGER
			MAX-ACCESS	read-only
			STATUS	current
			::= { hmWanMbus7C 96 }

hmWanMbus7CValue2D		OBJECT-TYPE
			SYNTAX	INTEGER
			MAX-ACCESS	read-only
			STATUS	current
			::= { hmWanMbus7C 97 }

hmWanMbus7CVIF2E		OBJECT-TYPE
			SYNTAX	INTEGER
			MAX-ACCESS	read-only
			STATUS	current
			::= { hmWanMbus7C 98 }

hmWanMbus7CValue2E		OBJECT-TYPE
			SYNTAX	INTEGER
			MAX-ACCESS	read-only
			STATUS	current
			::= { hmWanMbus7C 99 }

hmWanMbus7CVIF2F		OBJECT-TYPE
			SYNTAX	INTEGER
			MAX-ACCESS	read-only
			STATUS	current
			::= { hmWanMbus7C 100 }

hmWanMbus7CValue2F		OBJECT-TYPE
			SYNTAX	INTEGER
			MAX-ACCESS	read-only
			STATUS	current
			::= { hmWanMbus7C 101 }

hmWanMbus7D			OBJECT IDENTIFIER ::= { hmWanMbus 125 }

hmWanMbus7DIdNumber		OBJECT-TYPE
			SYNTAX	Gauge32
			MAX-ACCESS	read-only
			STATUS	current
			::= { hmWanMbus7D 1 }

hmWanMbus7DManufacturer	OBJECT-TYPE
			SYNTAX	Gauge32
			MAX-ACCESS	read-only
			STATUS	current
			::= { hmWanMbus7D 2 }

hmWanMbus7DVersion		OBJECT-TYPE
			SYNTAX	Gauge32
			MAX-ACCESS	read-only
			STATUS	current
			::= { hmWanMbus7D 3 }

hmWanMbus7DMedium		OBJECT-TYPE
			SYNTAX	Gauge32
			MAX-ACCESS	read-only
			STATUS	current
			::= { hmWanMbus7D 4 }

hmWanMbus7DStatus		OBJECT-TYPE
			SYNTAX	Gauge32
			MAX-ACCESS	read-only
			STATUS	current
			::= { hmWanMbus7D 5 }

hmWanMbus7DVIF00		OBJECT-TYPE
			SYNTAX	INTEGER
			MAX-ACCESS	read-only
			STATUS	current
			::= { hmWanMbus7D 6 }

hmWanMbus7DValue00		OBJECT-TYPE
			SYNTAX	INTEGER
			MAX-ACCESS	read-only
			STATUS	current
			::= { hmWanMbus7D 7 }

hmWanMbus7DVIF01		OBJECT-TYPE
			SYNTAX	INTEGER
			MAX-ACCESS	read-only
			STATUS	current
			::= { hmWanMbus7D 8 }

hmWanMbus7DValue01		OBJECT-TYPE
			SYNTAX	INTEGER
			MAX-ACCESS	read-only
			STATUS	current
			::= { hmWanMbus7D 9 }

hmWanMbus7DVIF02		OBJECT-TYPE
			SYNTAX	INTEGER
			MAX-ACCESS	read-only
			STATUS	current
			::= { hmWanMbus7D 10 }

hmWanMbus7DValue02		OBJECT-TYPE
			SYNTAX	INTEGER
			MAX-ACCESS	read-only
			STATUS	current
			::= { hmWanMbus7D 11 }

hmWanMbus7DVIF03		OBJECT-TYPE
			SYNTAX	INTEGER
			MAX-ACCESS	read-only
			STATUS	current
			::= { hmWanMbus7D 12 }

hmWanMbus7DValue03		OBJECT-TYPE
			SYNTAX	INTEGER
			MAX-ACCESS	read-only
			STATUS	current
			::= { hmWanMbus7D 13 }

hmWanMbus7DVIF04		OBJECT-TYPE
			SYNTAX	INTEGER
			MAX-ACCESS	read-only
			STATUS	current
			::= { hmWanMbus7D 14 }

hmWanMbus7DValue04		OBJECT-TYPE
			SYNTAX	INTEGER
			MAX-ACCESS	read-only
			STATUS	current
			::= { hmWanMbus7D 15 }

hmWanMbus7DVIF05		OBJECT-TYPE
			SYNTAX	INTEGER
			MAX-ACCESS	read-only
			STATUS	current
			::= { hmWanMbus7D 16 }

hmWanMbus7DValue05		OBJECT-TYPE
			SYNTAX	INTEGER
			MAX-ACCESS	read-only
			STATUS	current
			::= { hmWanMbus7D 17 }

hmWanMbus7DVIF06		OBJECT-TYPE
			SYNTAX	INTEGER
			MAX-ACCESS	read-only
			STATUS	current
			::= { hmWanMbus7D 18 }

hmWanMbus7DValue06		OBJECT-TYPE
			SYNTAX	INTEGER
			MAX-ACCESS	read-only
			STATUS	current
			::= { hmWanMbus7D 19 }

hmWanMbus7DVIF07		OBJECT-TYPE
			SYNTAX	INTEGER
			MAX-ACCESS	read-only
			STATUS	current
			::= { hmWanMbus7D 20 }

hmWanMbus7DValue07		OBJECT-TYPE
			SYNTAX	INTEGER
			MAX-ACCESS	read-only
			STATUS	current
			::= { hmWanMbus7D 21 }

hmWanMbus7DVIF08		OBJECT-TYPE
			SYNTAX	INTEGER
			MAX-ACCESS	read-only
			STATUS	current
			::= { hmWanMbus7D 22 }

hmWanMbus7DValue08		OBJECT-TYPE
			SYNTAX	INTEGER
			MAX-ACCESS	read-only
			STATUS	current
			::= { hmWanMbus7D 23 }

hmWanMbus7DVIF09		OBJECT-TYPE
			SYNTAX	INTEGER
			MAX-ACCESS	read-only
			STATUS	current
			::= { hmWanMbus7D 24 }

hmWanMbus7DValue09		OBJECT-TYPE
			SYNTAX	INTEGER
			MAX-ACCESS	read-only
			STATUS	current
			::= { hmWanMbus7D 25 }

hmWanMbus7DVIF0A		OBJECT-TYPE
			SYNTAX	INTEGER
			MAX-ACCESS	read-only
			STATUS	current
			::= { hmWanMbus7D 26 }

hmWanMbus7DValue0A		OBJECT-TYPE
			SYNTAX	INTEGER
			MAX-ACCESS	read-only
			STATUS	current
			::= { hmWanMbus7D 27 }

hmWanMbus7DVIF0B		OBJECT-TYPE
			SYNTAX	INTEGER
			MAX-ACCESS	read-only
			STATUS	current
			::= { hmWanMbus7D 28 }

hmWanMbus7DValue0B		OBJECT-TYPE
			SYNTAX	INTEGER
			MAX-ACCESS	read-only
			STATUS	current
			::= { hmWanMbus7D 29 }

hmWanMbus7DVIF0C		OBJECT-TYPE
			SYNTAX	INTEGER
			MAX-ACCESS	read-only
			STATUS	current
			::= { hmWanMbus7D 30 }

hmWanMbus7DValue0C		OBJECT-TYPE
			SYNTAX	INTEGER
			MAX-ACCESS	read-only
			STATUS	current
			::= { hmWanMbus7D 31 }

hmWanMbus7DVIF0D		OBJECT-TYPE
			SYNTAX	INTEGER
			MAX-ACCESS	read-only
			STATUS	current
			::= { hmWanMbus7D 32 }

hmWanMbus7DValue0D		OBJECT-TYPE
			SYNTAX	INTEGER
			MAX-ACCESS	read-only
			STATUS	current
			::= { hmWanMbus7D 33 }

hmWanMbus7DVIF0E		OBJECT-TYPE
			SYNTAX	INTEGER
			MAX-ACCESS	read-only
			STATUS	current
			::= { hmWanMbus7D 34 }

hmWanMbus7DValue0E		OBJECT-TYPE
			SYNTAX	INTEGER
			MAX-ACCESS	read-only
			STATUS	current
			::= { hmWanMbus7D 35 }

hmWanMbus7DVIF0F		OBJECT-TYPE
			SYNTAX	INTEGER
			MAX-ACCESS	read-only
			STATUS	current
			::= { hmWanMbus7D 36 }

hmWanMbus7DValue0F		OBJECT-TYPE
			SYNTAX	INTEGER
			MAX-ACCESS	read-only
			STATUS	current
			::= { hmWanMbus7D 37 }

hmWanMbus7DVIF10		OBJECT-TYPE
			SYNTAX	INTEGER
			MAX-ACCESS	read-only
			STATUS	current
			::= { hmWanMbus7D 38 }

hmWanMbus7DValue10		OBJECT-TYPE
			SYNTAX	INTEGER
			MAX-ACCESS	read-only
			STATUS	current
			::= { hmWanMbus7D 39 }

hmWanMbus7DVIF11		OBJECT-TYPE
			SYNTAX	INTEGER
			MAX-ACCESS	read-only
			STATUS	current
			::= { hmWanMbus7D 40 }

hmWanMbus7DValue11		OBJECT-TYPE
			SYNTAX	INTEGER
			MAX-ACCESS	read-only
			STATUS	current
			::= { hmWanMbus7D 41 }

hmWanMbus7DVIF12		OBJECT-TYPE
			SYNTAX	INTEGER
			MAX-ACCESS	read-only
			STATUS	current
			::= { hmWanMbus7D 42 }

hmWanMbus7DValue12		OBJECT-TYPE
			SYNTAX	INTEGER
			MAX-ACCESS	read-only
			STATUS	current
			::= { hmWanMbus7D 43 }

hmWanMbus7DVIF13		OBJECT-TYPE
			SYNTAX	INTEGER
			MAX-ACCESS	read-only
			STATUS	current
			::= { hmWanMbus7D 44 }

hmWanMbus7DValue13		OBJECT-TYPE
			SYNTAX	INTEGER
			MAX-ACCESS	read-only
			STATUS	current
			::= { hmWanMbus7D 45 }

hmWanMbus7DVIF14		OBJECT-TYPE
			SYNTAX	INTEGER
			MAX-ACCESS	read-only
			STATUS	current
			::= { hmWanMbus7D 46 }

hmWanMbus7DValue14		OBJECT-TYPE
			SYNTAX	INTEGER
			MAX-ACCESS	read-only
			STATUS	current
			::= { hmWanMbus7D 47 }

hmWanMbus7DVIF15		OBJECT-TYPE
			SYNTAX	INTEGER
			MAX-ACCESS	read-only
			STATUS	current
			::= { hmWanMbus7D 48 }

hmWanMbus7DValue15		OBJECT-TYPE
			SYNTAX	INTEGER
			MAX-ACCESS	read-only
			STATUS	current
			::= { hmWanMbus7D 49 }

hmWanMbus7DVIF16		OBJECT-TYPE
			SYNTAX	INTEGER
			MAX-ACCESS	read-only
			STATUS	current
			::= { hmWanMbus7D 50 }

hmWanMbus7DValue16		OBJECT-TYPE
			SYNTAX	INTEGER
			MAX-ACCESS	read-only
			STATUS	current
			::= { hmWanMbus7D 51 }

hmWanMbus7DVIF17		OBJECT-TYPE
			SYNTAX	INTEGER
			MAX-ACCESS	read-only
			STATUS	current
			::= { hmWanMbus7D 52 }

hmWanMbus7DValue17		OBJECT-TYPE
			SYNTAX	INTEGER
			MAX-ACCESS	read-only
			STATUS	current
			::= { hmWanMbus7D 53 }

hmWanMbus7DVIF18		OBJECT-TYPE
			SYNTAX	INTEGER
			MAX-ACCESS	read-only
			STATUS	current
			::= { hmWanMbus7D 54 }

hmWanMbus7DValue18		OBJECT-TYPE
			SYNTAX	INTEGER
			MAX-ACCESS	read-only
			STATUS	current
			::= { hmWanMbus7D 55 }

hmWanMbus7DVIF19		OBJECT-TYPE
			SYNTAX	INTEGER
			MAX-ACCESS	read-only
			STATUS	current
			::= { hmWanMbus7D 56 }

hmWanMbus7DValue19		OBJECT-TYPE
			SYNTAX	INTEGER
			MAX-ACCESS	read-only
			STATUS	current
			::= { hmWanMbus7D 57 }

hmWanMbus7DVIF1A		OBJECT-TYPE
			SYNTAX	INTEGER
			MAX-ACCESS	read-only
			STATUS	current
			::= { hmWanMbus7D 58 }

hmWanMbus7DValue1A		OBJECT-TYPE
			SYNTAX	INTEGER
			MAX-ACCESS	read-only
			STATUS	current
			::= { hmWanMbus7D 59 }

hmWanMbus7DVIF1B		OBJECT-TYPE
			SYNTAX	INTEGER
			MAX-ACCESS	read-only
			STATUS	current
			::= { hmWanMbus7D 60 }

hmWanMbus7DValue1B		OBJECT-TYPE
			SYNTAX	INTEGER
			MAX-ACCESS	read-only
			STATUS	current
			::= { hmWanMbus7D 61 }

hmWanMbus7DVIF1C		OBJECT-TYPE
			SYNTAX	INTEGER
			MAX-ACCESS	read-only
			STATUS	current
			::= { hmWanMbus7D 62 }

hmWanMbus7DValue1C		OBJECT-TYPE
			SYNTAX	INTEGER
			MAX-ACCESS	read-only
			STATUS	current
			::= { hmWanMbus7D 63 }

hmWanMbus7DVIF1D		OBJECT-TYPE
			SYNTAX	INTEGER
			MAX-ACCESS	read-only
			STATUS	current
			::= { hmWanMbus7D 64 }

hmWanMbus7DValue1D		OBJECT-TYPE
			SYNTAX	INTEGER
			MAX-ACCESS	read-only
			STATUS	current
			::= { hmWanMbus7D 65 }

hmWanMbus7DVIF1E		OBJECT-TYPE
			SYNTAX	INTEGER
			MAX-ACCESS	read-only
			STATUS	current
			::= { hmWanMbus7D 66 }

hmWanMbus7DValue1E		OBJECT-TYPE
			SYNTAX	INTEGER
			MAX-ACCESS	read-only
			STATUS	current
			::= { hmWanMbus7D 67 }

hmWanMbus7DVIF1F		OBJECT-TYPE
			SYNTAX	INTEGER
			MAX-ACCESS	read-only
			STATUS	current
			::= { hmWanMbus7D 68 }

hmWanMbus7DValue1F		OBJECT-TYPE
			SYNTAX	INTEGER
			MAX-ACCESS	read-only
			STATUS	current
			::= { hmWanMbus7D 69 }

hmWanMbus7DVIF20		OBJECT-TYPE
			SYNTAX	INTEGER
			MAX-ACCESS	read-only
			STATUS	current
			::= { hmWanMbus7D 70 }

hmWanMbus7DValue20		OBJECT-TYPE
			SYNTAX	INTEGER
			MAX-ACCESS	read-only
			STATUS	current
			::= { hmWanMbus7D 71 }

hmWanMbus7DVIF21		OBJECT-TYPE
			SYNTAX	INTEGER
			MAX-ACCESS	read-only
			STATUS	current
			::= { hmWanMbus7D 72 }

hmWanMbus7DValue21		OBJECT-TYPE
			SYNTAX	INTEGER
			MAX-ACCESS	read-only
			STATUS	current
			::= { hmWanMbus7D 73 }

hmWanMbus7DVIF22		OBJECT-TYPE
			SYNTAX	INTEGER
			MAX-ACCESS	read-only
			STATUS	current
			::= { hmWanMbus7D 74 }

hmWanMbus7DValue22		OBJECT-TYPE
			SYNTAX	INTEGER
			MAX-ACCESS	read-only
			STATUS	current
			::= { hmWanMbus7D 75 }

hmWanMbus7DVIF23		OBJECT-TYPE
			SYNTAX	INTEGER
			MAX-ACCESS	read-only
			STATUS	current
			::= { hmWanMbus7D 76 }

hmWanMbus7DValue23		OBJECT-TYPE
			SYNTAX	INTEGER
			MAX-ACCESS	read-only
			STATUS	current
			::= { hmWanMbus7D 77 }

hmWanMbus7DVIF24		OBJECT-TYPE
			SYNTAX	INTEGER
			MAX-ACCESS	read-only
			STATUS	current
			::= { hmWanMbus7D 78 }

hmWanMbus7DValue24		OBJECT-TYPE
			SYNTAX	INTEGER
			MAX-ACCESS	read-only
			STATUS	current
			::= { hmWanMbus7D 79 }

hmWanMbus7DVIF25		OBJECT-TYPE
			SYNTAX	INTEGER
			MAX-ACCESS	read-only
			STATUS	current
			::= { hmWanMbus7D 80 }

hmWanMbus7DValue25		OBJECT-TYPE
			SYNTAX	INTEGER
			MAX-ACCESS	read-only
			STATUS	current
			::= { hmWanMbus7D 81 }

hmWanMbus7DVIF26		OBJECT-TYPE
			SYNTAX	INTEGER
			MAX-ACCESS	read-only
			STATUS	current
			::= { hmWanMbus7D 82 }

hmWanMbus7DValue26		OBJECT-TYPE
			SYNTAX	INTEGER
			MAX-ACCESS	read-only
			STATUS	current
			::= { hmWanMbus7D 83 }

hmWanMbus7DVIF27		OBJECT-TYPE
			SYNTAX	INTEGER
			MAX-ACCESS	read-only
			STATUS	current
			::= { hmWanMbus7D 84 }

hmWanMbus7DValue27		OBJECT-TYPE
			SYNTAX	INTEGER
			MAX-ACCESS	read-only
			STATUS	current
			::= { hmWanMbus7D 85 }

hmWanMbus7DVIF28		OBJECT-TYPE
			SYNTAX	INTEGER
			MAX-ACCESS	read-only
			STATUS	current
			::= { hmWanMbus7D 86 }

hmWanMbus7DValue28		OBJECT-TYPE
			SYNTAX	INTEGER
			MAX-ACCESS	read-only
			STATUS	current
			::= { hmWanMbus7D 87 }

hmWanMbus7DVIF29		OBJECT-TYPE
			SYNTAX	INTEGER
			MAX-ACCESS	read-only
			STATUS	current
			::= { hmWanMbus7D 88 }

hmWanMbus7DValue29		OBJECT-TYPE
			SYNTAX	INTEGER
			MAX-ACCESS	read-only
			STATUS	current
			::= { hmWanMbus7D 89 }

hmWanMbus7DVIF2A		OBJECT-TYPE
			SYNTAX	INTEGER
			MAX-ACCESS	read-only
			STATUS	current
			::= { hmWanMbus7D 90 }

hmWanMbus7DValue2A		OBJECT-TYPE
			SYNTAX	INTEGER
			MAX-ACCESS	read-only
			STATUS	current
			::= { hmWanMbus7D 91 }

hmWanMbus7DVIF2B		OBJECT-TYPE
			SYNTAX	INTEGER
			MAX-ACCESS	read-only
			STATUS	current
			::= { hmWanMbus7D 92 }

hmWanMbus7DValue2B		OBJECT-TYPE
			SYNTAX	INTEGER
			MAX-ACCESS	read-only
			STATUS	current
			::= { hmWanMbus7D 93 }

hmWanMbus7DVIF2C		OBJECT-TYPE
			SYNTAX	INTEGER
			MAX-ACCESS	read-only
			STATUS	current
			::= { hmWanMbus7D 94 }

hmWanMbus7DValue2C		OBJECT-TYPE
			SYNTAX	INTEGER
			MAX-ACCESS	read-only
			STATUS	current
			::= { hmWanMbus7D 95 }

hmWanMbus7DVIF2D		OBJECT-TYPE
			SYNTAX	INTEGER
			MAX-ACCESS	read-only
			STATUS	current
			::= { hmWanMbus7D 96 }

hmWanMbus7DValue2D		OBJECT-TYPE
			SYNTAX	INTEGER
			MAX-ACCESS	read-only
			STATUS	current
			::= { hmWanMbus7D 97 }

hmWanMbus7DVIF2E		OBJECT-TYPE
			SYNTAX	INTEGER
			MAX-ACCESS	read-only
			STATUS	current
			::= { hmWanMbus7D 98 }

hmWanMbus7DValue2E		OBJECT-TYPE
			SYNTAX	INTEGER
			MAX-ACCESS	read-only
			STATUS	current
			::= { hmWanMbus7D 99 }

hmWanMbus7DVIF2F		OBJECT-TYPE
			SYNTAX	INTEGER
			MAX-ACCESS	read-only
			STATUS	current
			::= { hmWanMbus7D 100 }

hmWanMbus7DValue2F		OBJECT-TYPE
			SYNTAX	INTEGER
			MAX-ACCESS	read-only
			STATUS	current
			::= { hmWanMbus7D 101 }

hmWanMbus7E			OBJECT IDENTIFIER ::= { hmWanMbus 126 }

hmWanMbus7EIdNumber		OBJECT-TYPE
			SYNTAX	Gauge32
			MAX-ACCESS	read-only
			STATUS	current
			::= { hmWanMbus7E 1 }

hmWanMbus7EManufacturer	OBJECT-TYPE
			SYNTAX	Gauge32
			MAX-ACCESS	read-only
			STATUS	current
			::= { hmWanMbus7E 2 }

hmWanMbus7EVersion		OBJECT-TYPE
			SYNTAX	Gauge32
			MAX-ACCESS	read-only
			STATUS	current
			::= { hmWanMbus7E 3 }

hmWanMbus7EMedium		OBJECT-TYPE
			SYNTAX	Gauge32
			MAX-ACCESS	read-only
			STATUS	current
			::= { hmWanMbus7E 4 }

hmWanMbus7EStatus		OBJECT-TYPE
			SYNTAX	Gauge32
			MAX-ACCESS	read-only
			STATUS	current
			::= { hmWanMbus7E 5 }

hmWanMbus7EVIF00		OBJECT-TYPE
			SYNTAX	INTEGER
			MAX-ACCESS	read-only
			STATUS	current
			::= { hmWanMbus7E 6 }

hmWanMbus7EValue00		OBJECT-TYPE
			SYNTAX	INTEGER
			MAX-ACCESS	read-only
			STATUS	current
			::= { hmWanMbus7E 7 }

hmWanMbus7EVIF01		OBJECT-TYPE
			SYNTAX	INTEGER
			MAX-ACCESS	read-only
			STATUS	current
			::= { hmWanMbus7E 8 }

hmWanMbus7EValue01		OBJECT-TYPE
			SYNTAX	INTEGER
			MAX-ACCESS	read-only
			STATUS	current
			::= { hmWanMbus7E 9 }

hmWanMbus7EVIF02		OBJECT-TYPE
			SYNTAX	INTEGER
			MAX-ACCESS	read-only
			STATUS	current
			::= { hmWanMbus7E 10 }

hmWanMbus7EValue02		OBJECT-TYPE
			SYNTAX	INTEGER
			MAX-ACCESS	read-only
			STATUS	current
			::= { hmWanMbus7E 11 }

hmWanMbus7EVIF03		OBJECT-TYPE
			SYNTAX	INTEGER
			MAX-ACCESS	read-only
			STATUS	current
			::= { hmWanMbus7E 12 }

hmWanMbus7EValue03		OBJECT-TYPE
			SYNTAX	INTEGER
			MAX-ACCESS	read-only
			STATUS	current
			::= { hmWanMbus7E 13 }

hmWanMbus7EVIF04		OBJECT-TYPE
			SYNTAX	INTEGER
			MAX-ACCESS	read-only
			STATUS	current
			::= { hmWanMbus7E 14 }

hmWanMbus7EValue04		OBJECT-TYPE
			SYNTAX	INTEGER
			MAX-ACCESS	read-only
			STATUS	current
			::= { hmWanMbus7E 15 }

hmWanMbus7EVIF05		OBJECT-TYPE
			SYNTAX	INTEGER
			MAX-ACCESS	read-only
			STATUS	current
			::= { hmWanMbus7E 16 }

hmWanMbus7EValue05		OBJECT-TYPE
			SYNTAX	INTEGER
			MAX-ACCESS	read-only
			STATUS	current
			::= { hmWanMbus7E 17 }

hmWanMbus7EVIF06		OBJECT-TYPE
			SYNTAX	INTEGER
			MAX-ACCESS	read-only
			STATUS	current
			::= { hmWanMbus7E 18 }

hmWanMbus7EValue06		OBJECT-TYPE
			SYNTAX	INTEGER
			MAX-ACCESS	read-only
			STATUS	current
			::= { hmWanMbus7E 19 }

hmWanMbus7EVIF07		OBJECT-TYPE
			SYNTAX	INTEGER
			MAX-ACCESS	read-only
			STATUS	current
			::= { hmWanMbus7E 20 }

hmWanMbus7EValue07		OBJECT-TYPE
			SYNTAX	INTEGER
			MAX-ACCESS	read-only
			STATUS	current
			::= { hmWanMbus7E 21 }

hmWanMbus7EVIF08		OBJECT-TYPE
			SYNTAX	INTEGER
			MAX-ACCESS	read-only
			STATUS	current
			::= { hmWanMbus7E 22 }

hmWanMbus7EValue08		OBJECT-TYPE
			SYNTAX	INTEGER
			MAX-ACCESS	read-only
			STATUS	current
			::= { hmWanMbus7E 23 }

hmWanMbus7EVIF09		OBJECT-TYPE
			SYNTAX	INTEGER
			MAX-ACCESS	read-only
			STATUS	current
			::= { hmWanMbus7E 24 }

hmWanMbus7EValue09		OBJECT-TYPE
			SYNTAX	INTEGER
			MAX-ACCESS	read-only
			STATUS	current
			::= { hmWanMbus7E 25 }

hmWanMbus7EVIF0A		OBJECT-TYPE
			SYNTAX	INTEGER
			MAX-ACCESS	read-only
			STATUS	current
			::= { hmWanMbus7E 26 }

hmWanMbus7EValue0A		OBJECT-TYPE
			SYNTAX	INTEGER
			MAX-ACCESS	read-only
			STATUS	current
			::= { hmWanMbus7E 27 }

hmWanMbus7EVIF0B		OBJECT-TYPE
			SYNTAX	INTEGER
			MAX-ACCESS	read-only
			STATUS	current
			::= { hmWanMbus7E 28 }

hmWanMbus7EValue0B		OBJECT-TYPE
			SYNTAX	INTEGER
			MAX-ACCESS	read-only
			STATUS	current
			::= { hmWanMbus7E 29 }

hmWanMbus7EVIF0C		OBJECT-TYPE
			SYNTAX	INTEGER
			MAX-ACCESS	read-only
			STATUS	current
			::= { hmWanMbus7E 30 }

hmWanMbus7EValue0C		OBJECT-TYPE
			SYNTAX	INTEGER
			MAX-ACCESS	read-only
			STATUS	current
			::= { hmWanMbus7E 31 }

hmWanMbus7EVIF0D		OBJECT-TYPE
			SYNTAX	INTEGER
			MAX-ACCESS	read-only
			STATUS	current
			::= { hmWanMbus7E 32 }

hmWanMbus7EValue0D		OBJECT-TYPE
			SYNTAX	INTEGER
			MAX-ACCESS	read-only
			STATUS	current
			::= { hmWanMbus7E 33 }

hmWanMbus7EVIF0E		OBJECT-TYPE
			SYNTAX	INTEGER
			MAX-ACCESS	read-only
			STATUS	current
			::= { hmWanMbus7E 34 }

hmWanMbus7EValue0E		OBJECT-TYPE
			SYNTAX	INTEGER
			MAX-ACCESS	read-only
			STATUS	current
			::= { hmWanMbus7E 35 }

hmWanMbus7EVIF0F		OBJECT-TYPE
			SYNTAX	INTEGER
			MAX-ACCESS	read-only
			STATUS	current
			::= { hmWanMbus7E 36 }

hmWanMbus7EValue0F		OBJECT-TYPE
			SYNTAX	INTEGER
			MAX-ACCESS	read-only
			STATUS	current
			::= { hmWanMbus7E 37 }

hmWanMbus7EVIF10		OBJECT-TYPE
			SYNTAX	INTEGER
			MAX-ACCESS	read-only
			STATUS	current
			::= { hmWanMbus7E 38 }

hmWanMbus7EValue10		OBJECT-TYPE
			SYNTAX	INTEGER
			MAX-ACCESS	read-only
			STATUS	current
			::= { hmWanMbus7E 39 }

hmWanMbus7EVIF11		OBJECT-TYPE
			SYNTAX	INTEGER
			MAX-ACCESS	read-only
			STATUS	current
			::= { hmWanMbus7E 40 }

hmWanMbus7EValue11		OBJECT-TYPE
			SYNTAX	INTEGER
			MAX-ACCESS	read-only
			STATUS	current
			::= { hmWanMbus7E 41 }

hmWanMbus7EVIF12		OBJECT-TYPE
			SYNTAX	INTEGER
			MAX-ACCESS	read-only
			STATUS	current
			::= { hmWanMbus7E 42 }

hmWanMbus7EValue12		OBJECT-TYPE
			SYNTAX	INTEGER
			MAX-ACCESS	read-only
			STATUS	current
			::= { hmWanMbus7E 43 }

hmWanMbus7EVIF13		OBJECT-TYPE
			SYNTAX	INTEGER
			MAX-ACCESS	read-only
			STATUS	current
			::= { hmWanMbus7E 44 }

hmWanMbus7EValue13		OBJECT-TYPE
			SYNTAX	INTEGER
			MAX-ACCESS	read-only
			STATUS	current
			::= { hmWanMbus7E 45 }

hmWanMbus7EVIF14		OBJECT-TYPE
			SYNTAX	INTEGER
			MAX-ACCESS	read-only
			STATUS	current
			::= { hmWanMbus7E 46 }

hmWanMbus7EValue14		OBJECT-TYPE
			SYNTAX	INTEGER
			MAX-ACCESS	read-only
			STATUS	current
			::= { hmWanMbus7E 47 }

hmWanMbus7EVIF15		OBJECT-TYPE
			SYNTAX	INTEGER
			MAX-ACCESS	read-only
			STATUS	current
			::= { hmWanMbus7E 48 }

hmWanMbus7EValue15		OBJECT-TYPE
			SYNTAX	INTEGER
			MAX-ACCESS	read-only
			STATUS	current
			::= { hmWanMbus7E 49 }

hmWanMbus7EVIF16		OBJECT-TYPE
			SYNTAX	INTEGER
			MAX-ACCESS	read-only
			STATUS	current
			::= { hmWanMbus7E 50 }

hmWanMbus7EValue16		OBJECT-TYPE
			SYNTAX	INTEGER
			MAX-ACCESS	read-only
			STATUS	current
			::= { hmWanMbus7E 51 }

hmWanMbus7EVIF17		OBJECT-TYPE
			SYNTAX	INTEGER
			MAX-ACCESS	read-only
			STATUS	current
			::= { hmWanMbus7E 52 }

hmWanMbus7EValue17		OBJECT-TYPE
			SYNTAX	INTEGER
			MAX-ACCESS	read-only
			STATUS	current
			::= { hmWanMbus7E 53 }

hmWanMbus7EVIF18		OBJECT-TYPE
			SYNTAX	INTEGER
			MAX-ACCESS	read-only
			STATUS	current
			::= { hmWanMbus7E 54 }

hmWanMbus7EValue18		OBJECT-TYPE
			SYNTAX	INTEGER
			MAX-ACCESS	read-only
			STATUS	current
			::= { hmWanMbus7E 55 }

hmWanMbus7EVIF19		OBJECT-TYPE
			SYNTAX	INTEGER
			MAX-ACCESS	read-only
			STATUS	current
			::= { hmWanMbus7E 56 }

hmWanMbus7EValue19		OBJECT-TYPE
			SYNTAX	INTEGER
			MAX-ACCESS	read-only
			STATUS	current
			::= { hmWanMbus7E 57 }

hmWanMbus7EVIF1A		OBJECT-TYPE
			SYNTAX	INTEGER
			MAX-ACCESS	read-only
			STATUS	current
			::= { hmWanMbus7E 58 }

hmWanMbus7EValue1A		OBJECT-TYPE
			SYNTAX	INTEGER
			MAX-ACCESS	read-only
			STATUS	current
			::= { hmWanMbus7E 59 }

hmWanMbus7EVIF1B		OBJECT-TYPE
			SYNTAX	INTEGER
			MAX-ACCESS	read-only
			STATUS	current
			::= { hmWanMbus7E 60 }

hmWanMbus7EValue1B		OBJECT-TYPE
			SYNTAX	INTEGER
			MAX-ACCESS	read-only
			STATUS	current
			::= { hmWanMbus7E 61 }

hmWanMbus7EVIF1C		OBJECT-TYPE
			SYNTAX	INTEGER
			MAX-ACCESS	read-only
			STATUS	current
			::= { hmWanMbus7E 62 }

hmWanMbus7EValue1C		OBJECT-TYPE
			SYNTAX	INTEGER
			MAX-ACCESS	read-only
			STATUS	current
			::= { hmWanMbus7E 63 }

hmWanMbus7EVIF1D		OBJECT-TYPE
			SYNTAX	INTEGER
			MAX-ACCESS	read-only
			STATUS	current
			::= { hmWanMbus7E 64 }

hmWanMbus7EValue1D		OBJECT-TYPE
			SYNTAX	INTEGER
			MAX-ACCESS	read-only
			STATUS	current
			::= { hmWanMbus7E 65 }

hmWanMbus7EVIF1E		OBJECT-TYPE
			SYNTAX	INTEGER
			MAX-ACCESS	read-only
			STATUS	current
			::= { hmWanMbus7E 66 }

hmWanMbus7EValue1E		OBJECT-TYPE
			SYNTAX	INTEGER
			MAX-ACCESS	read-only
			STATUS	current
			::= { hmWanMbus7E 67 }

hmWanMbus7EVIF1F		OBJECT-TYPE
			SYNTAX	INTEGER
			MAX-ACCESS	read-only
			STATUS	current
			::= { hmWanMbus7E 68 }

hmWanMbus7EValue1F		OBJECT-TYPE
			SYNTAX	INTEGER
			MAX-ACCESS	read-only
			STATUS	current
			::= { hmWanMbus7E 69 }

hmWanMbus7EVIF20		OBJECT-TYPE
			SYNTAX	INTEGER
			MAX-ACCESS	read-only
			STATUS	current
			::= { hmWanMbus7E 70 }

hmWanMbus7EValue20		OBJECT-TYPE
			SYNTAX	INTEGER
			MAX-ACCESS	read-only
			STATUS	current
			::= { hmWanMbus7E 71 }

hmWanMbus7EVIF21		OBJECT-TYPE
			SYNTAX	INTEGER
			MAX-ACCESS	read-only
			STATUS	current
			::= { hmWanMbus7E 72 }

hmWanMbus7EValue21		OBJECT-TYPE
			SYNTAX	INTEGER
			MAX-ACCESS	read-only
			STATUS	current
			::= { hmWanMbus7E 73 }

hmWanMbus7EVIF22		OBJECT-TYPE
			SYNTAX	INTEGER
			MAX-ACCESS	read-only
			STATUS	current
			::= { hmWanMbus7E 74 }

hmWanMbus7EValue22		OBJECT-TYPE
			SYNTAX	INTEGER
			MAX-ACCESS	read-only
			STATUS	current
			::= { hmWanMbus7E 75 }

hmWanMbus7EVIF23		OBJECT-TYPE
			SYNTAX	INTEGER
			MAX-ACCESS	read-only
			STATUS	current
			::= { hmWanMbus7E 76 }

hmWanMbus7EValue23		OBJECT-TYPE
			SYNTAX	INTEGER
			MAX-ACCESS	read-only
			STATUS	current
			::= { hmWanMbus7E 77 }

hmWanMbus7EVIF24		OBJECT-TYPE
			SYNTAX	INTEGER
			MAX-ACCESS	read-only
			STATUS	current
			::= { hmWanMbus7E 78 }

hmWanMbus7EValue24		OBJECT-TYPE
			SYNTAX	INTEGER
			MAX-ACCESS	read-only
			STATUS	current
			::= { hmWanMbus7E 79 }

hmWanMbus7EVIF25		OBJECT-TYPE
			SYNTAX	INTEGER
			MAX-ACCESS	read-only
			STATUS	current
			::= { hmWanMbus7E 80 }

hmWanMbus7EValue25		OBJECT-TYPE
			SYNTAX	INTEGER
			MAX-ACCESS	read-only
			STATUS	current
			::= { hmWanMbus7E 81 }

hmWanMbus7EVIF26		OBJECT-TYPE
			SYNTAX	INTEGER
			MAX-ACCESS	read-only
			STATUS	current
			::= { hmWanMbus7E 82 }

hmWanMbus7EValue26		OBJECT-TYPE
			SYNTAX	INTEGER
			MAX-ACCESS	read-only
			STATUS	current
			::= { hmWanMbus7E 83 }

hmWanMbus7EVIF27		OBJECT-TYPE
			SYNTAX	INTEGER
			MAX-ACCESS	read-only
			STATUS	current
			::= { hmWanMbus7E 84 }

hmWanMbus7EValue27		OBJECT-TYPE
			SYNTAX	INTEGER
			MAX-ACCESS	read-only
			STATUS	current
			::= { hmWanMbus7E 85 }

hmWanMbus7EVIF28		OBJECT-TYPE
			SYNTAX	INTEGER
			MAX-ACCESS	read-only
			STATUS	current
			::= { hmWanMbus7E 86 }

hmWanMbus7EValue28		OBJECT-TYPE
			SYNTAX	INTEGER
			MAX-ACCESS	read-only
			STATUS	current
			::= { hmWanMbus7E 87 }

hmWanMbus7EVIF29		OBJECT-TYPE
			SYNTAX	INTEGER
			MAX-ACCESS	read-only
			STATUS	current
			::= { hmWanMbus7E 88 }

hmWanMbus7EValue29		OBJECT-TYPE
			SYNTAX	INTEGER
			MAX-ACCESS	read-only
			STATUS	current
			::= { hmWanMbus7E 89 }

hmWanMbus7EVIF2A		OBJECT-TYPE
			SYNTAX	INTEGER
			MAX-ACCESS	read-only
			STATUS	current
			::= { hmWanMbus7E 90 }

hmWanMbus7EValue2A		OBJECT-TYPE
			SYNTAX	INTEGER
			MAX-ACCESS	read-only
			STATUS	current
			::= { hmWanMbus7E 91 }

hmWanMbus7EVIF2B		OBJECT-TYPE
			SYNTAX	INTEGER
			MAX-ACCESS	read-only
			STATUS	current
			::= { hmWanMbus7E 92 }

hmWanMbus7EValue2B		OBJECT-TYPE
			SYNTAX	INTEGER
			MAX-ACCESS	read-only
			STATUS	current
			::= { hmWanMbus7E 93 }

hmWanMbus7EVIF2C		OBJECT-TYPE
			SYNTAX	INTEGER
			MAX-ACCESS	read-only
			STATUS	current
			::= { hmWanMbus7E 94 }

hmWanMbus7EValue2C		OBJECT-TYPE
			SYNTAX	INTEGER
			MAX-ACCESS	read-only
			STATUS	current
			::= { hmWanMbus7E 95 }

hmWanMbus7EVIF2D		OBJECT-TYPE
			SYNTAX	INTEGER
			MAX-ACCESS	read-only
			STATUS	current
			::= { hmWanMbus7E 96 }

hmWanMbus7EValue2D		OBJECT-TYPE
			SYNTAX	INTEGER
			MAX-ACCESS	read-only
			STATUS	current
			::= { hmWanMbus7E 97 }

hmWanMbus7EVIF2E		OBJECT-TYPE
			SYNTAX	INTEGER
			MAX-ACCESS	read-only
			STATUS	current
			::= { hmWanMbus7E 98 }

hmWanMbus7EValue2E		OBJECT-TYPE
			SYNTAX	INTEGER
			MAX-ACCESS	read-only
			STATUS	current
			::= { hmWanMbus7E 99 }

hmWanMbus7EVIF2F		OBJECT-TYPE
			SYNTAX	INTEGER
			MAX-ACCESS	read-only
			STATUS	current
			::= { hmWanMbus7E 100 }

hmWanMbus7EValue2F		OBJECT-TYPE
			SYNTAX	INTEGER
			MAX-ACCESS	read-only
			STATUS	current
			::= { hmWanMbus7E 101 }

hmWanMbus7F			OBJECT IDENTIFIER ::= { hmWanMbus 127 }

hmWanMbus7FIdNumber		OBJECT-TYPE
			SYNTAX	Gauge32
			MAX-ACCESS	read-only
			STATUS	current
			::= { hmWanMbus7F 1 }

hmWanMbus7FManufacturer	OBJECT-TYPE
			SYNTAX	Gauge32
			MAX-ACCESS	read-only
			STATUS	current
			::= { hmWanMbus7F 2 }

hmWanMbus7FVersion		OBJECT-TYPE
			SYNTAX	Gauge32
			MAX-ACCESS	read-only
			STATUS	current
			::= { hmWanMbus7F 3 }

hmWanMbus7FMedium		OBJECT-TYPE
			SYNTAX	Gauge32
			MAX-ACCESS	read-only
			STATUS	current
			::= { hmWanMbus7F 4 }

hmWanMbus7FStatus		OBJECT-TYPE
			SYNTAX	Gauge32
			MAX-ACCESS	read-only
			STATUS	current
			::= { hmWanMbus7F 5 }

hmWanMbus7FVIF00		OBJECT-TYPE
			SYNTAX	INTEGER
			MAX-ACCESS	read-only
			STATUS	current
			::= { hmWanMbus7F 6 }

hmWanMbus7FValue00		OBJECT-TYPE
			SYNTAX	INTEGER
			MAX-ACCESS	read-only
			STATUS	current
			::= { hmWanMbus7F 7 }

hmWanMbus7FVIF01		OBJECT-TYPE
			SYNTAX	INTEGER
			MAX-ACCESS	read-only
			STATUS	current
			::= { hmWanMbus7F 8 }

hmWanMbus7FValue01		OBJECT-TYPE
			SYNTAX	INTEGER
			MAX-ACCESS	read-only
			STATUS	current
			::= { hmWanMbus7F 9 }

hmWanMbus7FVIF02		OBJECT-TYPE
			SYNTAX	INTEGER
			MAX-ACCESS	read-only
			STATUS	current
			::= { hmWanMbus7F 10 }

hmWanMbus7FValue02		OBJECT-TYPE
			SYNTAX	INTEGER
			MAX-ACCESS	read-only
			STATUS	current
			::= { hmWanMbus7F 11 }

hmWanMbus7FVIF03		OBJECT-TYPE
			SYNTAX	INTEGER
			MAX-ACCESS	read-only
			STATUS	current
			::= { hmWanMbus7F 12 }

hmWanMbus7FValue03		OBJECT-TYPE
			SYNTAX	INTEGER
			MAX-ACCESS	read-only
			STATUS	current
			::= { hmWanMbus7F 13 }

hmWanMbus7FVIF04		OBJECT-TYPE
			SYNTAX	INTEGER
			MAX-ACCESS	read-only
			STATUS	current
			::= { hmWanMbus7F 14 }

hmWanMbus7FValue04		OBJECT-TYPE
			SYNTAX	INTEGER
			MAX-ACCESS	read-only
			STATUS	current
			::= { hmWanMbus7F 15 }

hmWanMbus7FVIF05		OBJECT-TYPE
			SYNTAX	INTEGER
			MAX-ACCESS	read-only
			STATUS	current
			::= { hmWanMbus7F 16 }

hmWanMbus7FValue05		OBJECT-TYPE
			SYNTAX	INTEGER
			MAX-ACCESS	read-only
			STATUS	current
			::= { hmWanMbus7F 17 }

hmWanMbus7FVIF06		OBJECT-TYPE
			SYNTAX	INTEGER
			MAX-ACCESS	read-only
			STATUS	current
			::= { hmWanMbus7F 18 }

hmWanMbus7FValue06		OBJECT-TYPE
			SYNTAX	INTEGER
			MAX-ACCESS	read-only
			STATUS	current
			::= { hmWanMbus7F 19 }

hmWanMbus7FVIF07		OBJECT-TYPE
			SYNTAX	INTEGER
			MAX-ACCESS	read-only
			STATUS	current
			::= { hmWanMbus7F 20 }

hmWanMbus7FValue07		OBJECT-TYPE
			SYNTAX	INTEGER
			MAX-ACCESS	read-only
			STATUS	current
			::= { hmWanMbus7F 21 }

hmWanMbus7FVIF08		OBJECT-TYPE
			SYNTAX	INTEGER
			MAX-ACCESS	read-only
			STATUS	current
			::= { hmWanMbus7F 22 }

hmWanMbus7FValue08		OBJECT-TYPE
			SYNTAX	INTEGER
			MAX-ACCESS	read-only
			STATUS	current
			::= { hmWanMbus7F 23 }

hmWanMbus7FVIF09		OBJECT-TYPE
			SYNTAX	INTEGER
			MAX-ACCESS	read-only
			STATUS	current
			::= { hmWanMbus7F 24 }

hmWanMbus7FValue09		OBJECT-TYPE
			SYNTAX	INTEGER
			MAX-ACCESS	read-only
			STATUS	current
			::= { hmWanMbus7F 25 }

hmWanMbus7FVIF0A		OBJECT-TYPE
			SYNTAX	INTEGER
			MAX-ACCESS	read-only
			STATUS	current
			::= { hmWanMbus7F 26 }

hmWanMbus7FValue0A		OBJECT-TYPE
			SYNTAX	INTEGER
			MAX-ACCESS	read-only
			STATUS	current
			::= { hmWanMbus7F 27 }

hmWanMbus7FVIF0B		OBJECT-TYPE
			SYNTAX	INTEGER
			MAX-ACCESS	read-only
			STATUS	current
			::= { hmWanMbus7F 28 }

hmWanMbus7FValue0B		OBJECT-TYPE
			SYNTAX	INTEGER
			MAX-ACCESS	read-only
			STATUS	current
			::= { hmWanMbus7F 29 }

hmWanMbus7FVIF0C		OBJECT-TYPE
			SYNTAX	INTEGER
			MAX-ACCESS	read-only
			STATUS	current
			::= { hmWanMbus7F 30 }

hmWanMbus7FValue0C		OBJECT-TYPE
			SYNTAX	INTEGER
			MAX-ACCESS	read-only
			STATUS	current
			::= { hmWanMbus7F 31 }

hmWanMbus7FVIF0D		OBJECT-TYPE
			SYNTAX	INTEGER
			MAX-ACCESS	read-only
			STATUS	current
			::= { hmWanMbus7F 32 }

hmWanMbus7FValue0D		OBJECT-TYPE
			SYNTAX	INTEGER
			MAX-ACCESS	read-only
			STATUS	current
			::= { hmWanMbus7F 33 }

hmWanMbus7FVIF0E		OBJECT-TYPE
			SYNTAX	INTEGER
			MAX-ACCESS	read-only
			STATUS	current
			::= { hmWanMbus7F 34 }

hmWanMbus7FValue0E		OBJECT-TYPE
			SYNTAX	INTEGER
			MAX-ACCESS	read-only
			STATUS	current
			::= { hmWanMbus7F 35 }

hmWanMbus7FVIF0F		OBJECT-TYPE
			SYNTAX	INTEGER
			MAX-ACCESS	read-only
			STATUS	current
			::= { hmWanMbus7F 36 }

hmWanMbus7FValue0F		OBJECT-TYPE
			SYNTAX	INTEGER
			MAX-ACCESS	read-only
			STATUS	current
			::= { hmWanMbus7F 37 }

hmWanMbus7FVIF10		OBJECT-TYPE
			SYNTAX	INTEGER
			MAX-ACCESS	read-only
			STATUS	current
			::= { hmWanMbus7F 38 }

hmWanMbus7FValue10		OBJECT-TYPE
			SYNTAX	INTEGER
			MAX-ACCESS	read-only
			STATUS	current
			::= { hmWanMbus7F 39 }

hmWanMbus7FVIF11		OBJECT-TYPE
			SYNTAX	INTEGER
			MAX-ACCESS	read-only
			STATUS	current
			::= { hmWanMbus7F 40 }

hmWanMbus7FValue11		OBJECT-TYPE
			SYNTAX	INTEGER
			MAX-ACCESS	read-only
			STATUS	current
			::= { hmWanMbus7F 41 }

hmWanMbus7FVIF12		OBJECT-TYPE
			SYNTAX	INTEGER
			MAX-ACCESS	read-only
			STATUS	current
			::= { hmWanMbus7F 42 }

hmWanMbus7FValue12		OBJECT-TYPE
			SYNTAX	INTEGER
			MAX-ACCESS	read-only
			STATUS	current
			::= { hmWanMbus7F 43 }

hmWanMbus7FVIF13		OBJECT-TYPE
			SYNTAX	INTEGER
			MAX-ACCESS	read-only
			STATUS	current
			::= { hmWanMbus7F 44 }

hmWanMbus7FValue13		OBJECT-TYPE
			SYNTAX	INTEGER
			MAX-ACCESS	read-only
			STATUS	current
			::= { hmWanMbus7F 45 }

hmWanMbus7FVIF14		OBJECT-TYPE
			SYNTAX	INTEGER
			MAX-ACCESS	read-only
			STATUS	current
			::= { hmWanMbus7F 46 }

hmWanMbus7FValue14		OBJECT-TYPE
			SYNTAX	INTEGER
			MAX-ACCESS	read-only
			STATUS	current
			::= { hmWanMbus7F 47 }

hmWanMbus7FVIF15		OBJECT-TYPE
			SYNTAX	INTEGER
			MAX-ACCESS	read-only
			STATUS	current
			::= { hmWanMbus7F 48 }

hmWanMbus7FValue15		OBJECT-TYPE
			SYNTAX	INTEGER
			MAX-ACCESS	read-only
			STATUS	current
			::= { hmWanMbus7F 49 }

hmWanMbus7FVIF16		OBJECT-TYPE
			SYNTAX	INTEGER
			MAX-ACCESS	read-only
			STATUS	current
			::= { hmWanMbus7F 50 }

hmWanMbus7FValue16		OBJECT-TYPE
			SYNTAX	INTEGER
			MAX-ACCESS	read-only
			STATUS	current
			::= { hmWanMbus7F 51 }

hmWanMbus7FVIF17		OBJECT-TYPE
			SYNTAX	INTEGER
			MAX-ACCESS	read-only
			STATUS	current
			::= { hmWanMbus7F 52 }

hmWanMbus7FValue17		OBJECT-TYPE
			SYNTAX	INTEGER
			MAX-ACCESS	read-only
			STATUS	current
			::= { hmWanMbus7F 53 }

hmWanMbus7FVIF18		OBJECT-TYPE
			SYNTAX	INTEGER
			MAX-ACCESS	read-only
			STATUS	current
			::= { hmWanMbus7F 54 }

hmWanMbus7FValue18		OBJECT-TYPE
			SYNTAX	INTEGER
			MAX-ACCESS	read-only
			STATUS	current
			::= { hmWanMbus7F 55 }

hmWanMbus7FVIF19		OBJECT-TYPE
			SYNTAX	INTEGER
			MAX-ACCESS	read-only
			STATUS	current
			::= { hmWanMbus7F 56 }

hmWanMbus7FValue19		OBJECT-TYPE
			SYNTAX	INTEGER
			MAX-ACCESS	read-only
			STATUS	current
			::= { hmWanMbus7F 57 }

hmWanMbus7FVIF1A		OBJECT-TYPE
			SYNTAX	INTEGER
			MAX-ACCESS	read-only
			STATUS	current
			::= { hmWanMbus7F 58 }

hmWanMbus7FValue1A		OBJECT-TYPE
			SYNTAX	INTEGER
			MAX-ACCESS	read-only
			STATUS	current
			::= { hmWanMbus7F 59 }

hmWanMbus7FVIF1B		OBJECT-TYPE
			SYNTAX	INTEGER
			MAX-ACCESS	read-only
			STATUS	current
			::= { hmWanMbus7F 60 }

hmWanMbus7FValue1B		OBJECT-TYPE
			SYNTAX	INTEGER
			MAX-ACCESS	read-only
			STATUS	current
			::= { hmWanMbus7F 61 }

hmWanMbus7FVIF1C		OBJECT-TYPE
			SYNTAX	INTEGER
			MAX-ACCESS	read-only
			STATUS	current
			::= { hmWanMbus7F 62 }

hmWanMbus7FValue1C		OBJECT-TYPE
			SYNTAX	INTEGER
			MAX-ACCESS	read-only
			STATUS	current
			::= { hmWanMbus7F 63 }

hmWanMbus7FVIF1D		OBJECT-TYPE
			SYNTAX	INTEGER
			MAX-ACCESS	read-only
			STATUS	current
			::= { hmWanMbus7F 64 }

hmWanMbus7FValue1D		OBJECT-TYPE
			SYNTAX	INTEGER
			MAX-ACCESS	read-only
			STATUS	current
			::= { hmWanMbus7F 65 }

hmWanMbus7FVIF1E		OBJECT-TYPE
			SYNTAX	INTEGER
			MAX-ACCESS	read-only
			STATUS	current
			::= { hmWanMbus7F 66 }

hmWanMbus7FValue1E		OBJECT-TYPE
			SYNTAX	INTEGER
			MAX-ACCESS	read-only
			STATUS	current
			::= { hmWanMbus7F 67 }

hmWanMbus7FVIF1F		OBJECT-TYPE
			SYNTAX	INTEGER
			MAX-ACCESS	read-only
			STATUS	current
			::= { hmWanMbus7F 68 }

hmWanMbus7FValue1F		OBJECT-TYPE
			SYNTAX	INTEGER
			MAX-ACCESS	read-only
			STATUS	current
			::= { hmWanMbus7F 69 }

hmWanMbus7FVIF20		OBJECT-TYPE
			SYNTAX	INTEGER
			MAX-ACCESS	read-only
			STATUS	current
			::= { hmWanMbus7F 70 }

hmWanMbus7FValue20		OBJECT-TYPE
			SYNTAX	INTEGER
			MAX-ACCESS	read-only
			STATUS	current
			::= { hmWanMbus7F 71 }

hmWanMbus7FVIF21		OBJECT-TYPE
			SYNTAX	INTEGER
			MAX-ACCESS	read-only
			STATUS	current
			::= { hmWanMbus7F 72 }

hmWanMbus7FValue21		OBJECT-TYPE
			SYNTAX	INTEGER
			MAX-ACCESS	read-only
			STATUS	current
			::= { hmWanMbus7F 73 }

hmWanMbus7FVIF22		OBJECT-TYPE
			SYNTAX	INTEGER
			MAX-ACCESS	read-only
			STATUS	current
			::= { hmWanMbus7F 74 }

hmWanMbus7FValue22		OBJECT-TYPE
			SYNTAX	INTEGER
			MAX-ACCESS	read-only
			STATUS	current
			::= { hmWanMbus7F 75 }

hmWanMbus7FVIF23		OBJECT-TYPE
			SYNTAX	INTEGER
			MAX-ACCESS	read-only
			STATUS	current
			::= { hmWanMbus7F 76 }

hmWanMbus7FValue23		OBJECT-TYPE
			SYNTAX	INTEGER
			MAX-ACCESS	read-only
			STATUS	current
			::= { hmWanMbus7F 77 }

hmWanMbus7FVIF24		OBJECT-TYPE
			SYNTAX	INTEGER
			MAX-ACCESS	read-only
			STATUS	current
			::= { hmWanMbus7F 78 }

hmWanMbus7FValue24		OBJECT-TYPE
			SYNTAX	INTEGER
			MAX-ACCESS	read-only
			STATUS	current
			::= { hmWanMbus7F 79 }

hmWanMbus7FVIF25		OBJECT-TYPE
			SYNTAX	INTEGER
			MAX-ACCESS	read-only
			STATUS	current
			::= { hmWanMbus7F 80 }

hmWanMbus7FValue25		OBJECT-TYPE
			SYNTAX	INTEGER
			MAX-ACCESS	read-only
			STATUS	current
			::= { hmWanMbus7F 81 }

hmWanMbus7FVIF26		OBJECT-TYPE
			SYNTAX	INTEGER
			MAX-ACCESS	read-only
			STATUS	current
			::= { hmWanMbus7F 82 }

hmWanMbus7FValue26		OBJECT-TYPE
			SYNTAX	INTEGER
			MAX-ACCESS	read-only
			STATUS	current
			::= { hmWanMbus7F 83 }

hmWanMbus7FVIF27		OBJECT-TYPE
			SYNTAX	INTEGER
			MAX-ACCESS	read-only
			STATUS	current
			::= { hmWanMbus7F 84 }

hmWanMbus7FValue27		OBJECT-TYPE
			SYNTAX	INTEGER
			MAX-ACCESS	read-only
			STATUS	current
			::= { hmWanMbus7F 85 }

hmWanMbus7FVIF28		OBJECT-TYPE
			SYNTAX	INTEGER
			MAX-ACCESS	read-only
			STATUS	current
			::= { hmWanMbus7F 86 }

hmWanMbus7FValue28		OBJECT-TYPE
			SYNTAX	INTEGER
			MAX-ACCESS	read-only
			STATUS	current
			::= { hmWanMbus7F 87 }

hmWanMbus7FVIF29		OBJECT-TYPE
			SYNTAX	INTEGER
			MAX-ACCESS	read-only
			STATUS	current
			::= { hmWanMbus7F 88 }

hmWanMbus7FValue29		OBJECT-TYPE
			SYNTAX	INTEGER
			MAX-ACCESS	read-only
			STATUS	current
			::= { hmWanMbus7F 89 }

hmWanMbus7FVIF2A		OBJECT-TYPE
			SYNTAX	INTEGER
			MAX-ACCESS	read-only
			STATUS	current
			::= { hmWanMbus7F 90 }

hmWanMbus7FValue2A		OBJECT-TYPE
			SYNTAX	INTEGER
			MAX-ACCESS	read-only
			STATUS	current
			::= { hmWanMbus7F 91 }

hmWanMbus7FVIF2B		OBJECT-TYPE
			SYNTAX	INTEGER
			MAX-ACCESS	read-only
			STATUS	current
			::= { hmWanMbus7F 92 }

hmWanMbus7FValue2B		OBJECT-TYPE
			SYNTAX	INTEGER
			MAX-ACCESS	read-only
			STATUS	current
			::= { hmWanMbus7F 93 }

hmWanMbus7FVIF2C		OBJECT-TYPE
			SYNTAX	INTEGER
			MAX-ACCESS	read-only
			STATUS	current
			::= { hmWanMbus7F 94 }

hmWanMbus7FValue2C		OBJECT-TYPE
			SYNTAX	INTEGER
			MAX-ACCESS	read-only
			STATUS	current
			::= { hmWanMbus7F 95 }

hmWanMbus7FVIF2D		OBJECT-TYPE
			SYNTAX	INTEGER
			MAX-ACCESS	read-only
			STATUS	current
			::= { hmWanMbus7F 96 }

hmWanMbus7FValue2D		OBJECT-TYPE
			SYNTAX	INTEGER
			MAX-ACCESS	read-only
			STATUS	current
			::= { hmWanMbus7F 97 }

hmWanMbus7FVIF2E		OBJECT-TYPE
			SYNTAX	INTEGER
			MAX-ACCESS	read-only
			STATUS	current
			::= { hmWanMbus7F 98 }

hmWanMbus7FValue2E		OBJECT-TYPE
			SYNTAX	INTEGER
			MAX-ACCESS	read-only
			STATUS	current
			::= { hmWanMbus7F 99 }

hmWanMbus7FVIF2F		OBJECT-TYPE
			SYNTAX	INTEGER
			MAX-ACCESS	read-only
			STATUS	current
			::= { hmWanMbus7F 100 }

hmWanMbus7FValue2F		OBJECT-TYPE
			SYNTAX	INTEGER
			MAX-ACCESS	read-only
			STATUS	current
			::= { hmWanMbus7F 101 }

hmWanMbus80			OBJECT IDENTIFIER ::= { hmWanMbus 128 }

hmWanMbus80IdNumber		OBJECT-TYPE
			SYNTAX	Gauge32
			MAX-ACCESS	read-only
			STATUS	current
			::= { hmWanMbus80 1 }

hmWanMbus80Manufacturer	OBJECT-TYPE
			SYNTAX	Gauge32
			MAX-ACCESS	read-only
			STATUS	current
			::= { hmWanMbus80 2 }

hmWanMbus80Version		OBJECT-TYPE
			SYNTAX	Gauge32
			MAX-ACCESS	read-only
			STATUS	current
			::= { hmWanMbus80 3 }

hmWanMbus80Medium		OBJECT-TYPE
			SYNTAX	Gauge32
			MAX-ACCESS	read-only
			STATUS	current
			::= { hmWanMbus80 4 }

hmWanMbus80Status		OBJECT-TYPE
			SYNTAX	Gauge32
			MAX-ACCESS	read-only
			STATUS	current
			::= { hmWanMbus80 5 }

hmWanMbus80VIF00		OBJECT-TYPE
			SYNTAX	INTEGER
			MAX-ACCESS	read-only
			STATUS	current
			::= { hmWanMbus80 6 }

hmWanMbus80Value00		OBJECT-TYPE
			SYNTAX	INTEGER
			MAX-ACCESS	read-only
			STATUS	current
			::= { hmWanMbus80 7 }

hmWanMbus80VIF01		OBJECT-TYPE
			SYNTAX	INTEGER
			MAX-ACCESS	read-only
			STATUS	current
			::= { hmWanMbus80 8 }

hmWanMbus80Value01		OBJECT-TYPE
			SYNTAX	INTEGER
			MAX-ACCESS	read-only
			STATUS	current
			::= { hmWanMbus80 9 }

hmWanMbus80VIF02		OBJECT-TYPE
			SYNTAX	INTEGER
			MAX-ACCESS	read-only
			STATUS	current
			::= { hmWanMbus80 10 }

hmWanMbus80Value02		OBJECT-TYPE
			SYNTAX	INTEGER
			MAX-ACCESS	read-only
			STATUS	current
			::= { hmWanMbus80 11 }

hmWanMbus80VIF03		OBJECT-TYPE
			SYNTAX	INTEGER
			MAX-ACCESS	read-only
			STATUS	current
			::= { hmWanMbus80 12 }

hmWanMbus80Value03		OBJECT-TYPE
			SYNTAX	INTEGER
			MAX-ACCESS	read-only
			STATUS	current
			::= { hmWanMbus80 13 }

hmWanMbus80VIF04		OBJECT-TYPE
			SYNTAX	INTEGER
			MAX-ACCESS	read-only
			STATUS	current
			::= { hmWanMbus80 14 }

hmWanMbus80Value04		OBJECT-TYPE
			SYNTAX	INTEGER
			MAX-ACCESS	read-only
			STATUS	current
			::= { hmWanMbus80 15 }

hmWanMbus80VIF05		OBJECT-TYPE
			SYNTAX	INTEGER
			MAX-ACCESS	read-only
			STATUS	current
			::= { hmWanMbus80 16 }

hmWanMbus80Value05		OBJECT-TYPE
			SYNTAX	INTEGER
			MAX-ACCESS	read-only
			STATUS	current
			::= { hmWanMbus80 17 }

hmWanMbus80VIF06		OBJECT-TYPE
			SYNTAX	INTEGER
			MAX-ACCESS	read-only
			STATUS	current
			::= { hmWanMbus80 18 }

hmWanMbus80Value06		OBJECT-TYPE
			SYNTAX	INTEGER
			MAX-ACCESS	read-only
			STATUS	current
			::= { hmWanMbus80 19 }

hmWanMbus80VIF07		OBJECT-TYPE
			SYNTAX	INTEGER
			MAX-ACCESS	read-only
			STATUS	current
			::= { hmWanMbus80 20 }

hmWanMbus80Value07		OBJECT-TYPE
			SYNTAX	INTEGER
			MAX-ACCESS	read-only
			STATUS	current
			::= { hmWanMbus80 21 }

hmWanMbus80VIF08		OBJECT-TYPE
			SYNTAX	INTEGER
			MAX-ACCESS	read-only
			STATUS	current
			::= { hmWanMbus80 22 }

hmWanMbus80Value08		OBJECT-TYPE
			SYNTAX	INTEGER
			MAX-ACCESS	read-only
			STATUS	current
			::= { hmWanMbus80 23 }

hmWanMbus80VIF09		OBJECT-TYPE
			SYNTAX	INTEGER
			MAX-ACCESS	read-only
			STATUS	current
			::= { hmWanMbus80 24 }

hmWanMbus80Value09		OBJECT-TYPE
			SYNTAX	INTEGER
			MAX-ACCESS	read-only
			STATUS	current
			::= { hmWanMbus80 25 }

hmWanMbus80VIF0A		OBJECT-TYPE
			SYNTAX	INTEGER
			MAX-ACCESS	read-only
			STATUS	current
			::= { hmWanMbus80 26 }

hmWanMbus80Value0A		OBJECT-TYPE
			SYNTAX	INTEGER
			MAX-ACCESS	read-only
			STATUS	current
			::= { hmWanMbus80 27 }

hmWanMbus80VIF0B		OBJECT-TYPE
			SYNTAX	INTEGER
			MAX-ACCESS	read-only
			STATUS	current
			::= { hmWanMbus80 28 }

hmWanMbus80Value0B		OBJECT-TYPE
			SYNTAX	INTEGER
			MAX-ACCESS	read-only
			STATUS	current
			::= { hmWanMbus80 29 }

hmWanMbus80VIF0C		OBJECT-TYPE
			SYNTAX	INTEGER
			MAX-ACCESS	read-only
			STATUS	current
			::= { hmWanMbus80 30 }

hmWanMbus80Value0C		OBJECT-TYPE
			SYNTAX	INTEGER
			MAX-ACCESS	read-only
			STATUS	current
			::= { hmWanMbus80 31 }

hmWanMbus80VIF0D		OBJECT-TYPE
			SYNTAX	INTEGER
			MAX-ACCESS	read-only
			STATUS	current
			::= { hmWanMbus80 32 }

hmWanMbus80Value0D		OBJECT-TYPE
			SYNTAX	INTEGER
			MAX-ACCESS	read-only
			STATUS	current
			::= { hmWanMbus80 33 }

hmWanMbus80VIF0E		OBJECT-TYPE
			SYNTAX	INTEGER
			MAX-ACCESS	read-only
			STATUS	current
			::= { hmWanMbus80 34 }

hmWanMbus80Value0E		OBJECT-TYPE
			SYNTAX	INTEGER
			MAX-ACCESS	read-only
			STATUS	current
			::= { hmWanMbus80 35 }

hmWanMbus80VIF0F		OBJECT-TYPE
			SYNTAX	INTEGER
			MAX-ACCESS	read-only
			STATUS	current
			::= { hmWanMbus80 36 }

hmWanMbus80Value0F		OBJECT-TYPE
			SYNTAX	INTEGER
			MAX-ACCESS	read-only
			STATUS	current
			::= { hmWanMbus80 37 }

hmWanMbus80VIF10		OBJECT-TYPE
			SYNTAX	INTEGER
			MAX-ACCESS	read-only
			STATUS	current
			::= { hmWanMbus80 38 }

hmWanMbus80Value10		OBJECT-TYPE
			SYNTAX	INTEGER
			MAX-ACCESS	read-only
			STATUS	current
			::= { hmWanMbus80 39 }

hmWanMbus80VIF11		OBJECT-TYPE
			SYNTAX	INTEGER
			MAX-ACCESS	read-only
			STATUS	current
			::= { hmWanMbus80 40 }

hmWanMbus80Value11		OBJECT-TYPE
			SYNTAX	INTEGER
			MAX-ACCESS	read-only
			STATUS	current
			::= { hmWanMbus80 41 }

hmWanMbus80VIF12		OBJECT-TYPE
			SYNTAX	INTEGER
			MAX-ACCESS	read-only
			STATUS	current
			::= { hmWanMbus80 42 }

hmWanMbus80Value12		OBJECT-TYPE
			SYNTAX	INTEGER
			MAX-ACCESS	read-only
			STATUS	current
			::= { hmWanMbus80 43 }

hmWanMbus80VIF13		OBJECT-TYPE
			SYNTAX	INTEGER
			MAX-ACCESS	read-only
			STATUS	current
			::= { hmWanMbus80 44 }

hmWanMbus80Value13		OBJECT-TYPE
			SYNTAX	INTEGER
			MAX-ACCESS	read-only
			STATUS	current
			::= { hmWanMbus80 45 }

hmWanMbus80VIF14		OBJECT-TYPE
			SYNTAX	INTEGER
			MAX-ACCESS	read-only
			STATUS	current
			::= { hmWanMbus80 46 }

hmWanMbus80Value14		OBJECT-TYPE
			SYNTAX	INTEGER
			MAX-ACCESS	read-only
			STATUS	current
			::= { hmWanMbus80 47 }

hmWanMbus80VIF15		OBJECT-TYPE
			SYNTAX	INTEGER
			MAX-ACCESS	read-only
			STATUS	current
			::= { hmWanMbus80 48 }

hmWanMbus80Value15		OBJECT-TYPE
			SYNTAX	INTEGER
			MAX-ACCESS	read-only
			STATUS	current
			::= { hmWanMbus80 49 }

hmWanMbus80VIF16		OBJECT-TYPE
			SYNTAX	INTEGER
			MAX-ACCESS	read-only
			STATUS	current
			::= { hmWanMbus80 50 }

hmWanMbus80Value16		OBJECT-TYPE
			SYNTAX	INTEGER
			MAX-ACCESS	read-only
			STATUS	current
			::= { hmWanMbus80 51 }

hmWanMbus80VIF17		OBJECT-TYPE
			SYNTAX	INTEGER
			MAX-ACCESS	read-only
			STATUS	current
			::= { hmWanMbus80 52 }

hmWanMbus80Value17		OBJECT-TYPE
			SYNTAX	INTEGER
			MAX-ACCESS	read-only
			STATUS	current
			::= { hmWanMbus80 53 }

hmWanMbus80VIF18		OBJECT-TYPE
			SYNTAX	INTEGER
			MAX-ACCESS	read-only
			STATUS	current
			::= { hmWanMbus80 54 }

hmWanMbus80Value18		OBJECT-TYPE
			SYNTAX	INTEGER
			MAX-ACCESS	read-only
			STATUS	current
			::= { hmWanMbus80 55 }

hmWanMbus80VIF19		OBJECT-TYPE
			SYNTAX	INTEGER
			MAX-ACCESS	read-only
			STATUS	current
			::= { hmWanMbus80 56 }

hmWanMbus80Value19		OBJECT-TYPE
			SYNTAX	INTEGER
			MAX-ACCESS	read-only
			STATUS	current
			::= { hmWanMbus80 57 }

hmWanMbus80VIF1A		OBJECT-TYPE
			SYNTAX	INTEGER
			MAX-ACCESS	read-only
			STATUS	current
			::= { hmWanMbus80 58 }

hmWanMbus80Value1A		OBJECT-TYPE
			SYNTAX	INTEGER
			MAX-ACCESS	read-only
			STATUS	current
			::= { hmWanMbus80 59 }

hmWanMbus80VIF1B		OBJECT-TYPE
			SYNTAX	INTEGER
			MAX-ACCESS	read-only
			STATUS	current
			::= { hmWanMbus80 60 }

hmWanMbus80Value1B		OBJECT-TYPE
			SYNTAX	INTEGER
			MAX-ACCESS	read-only
			STATUS	current
			::= { hmWanMbus80 61 }

hmWanMbus80VIF1C		OBJECT-TYPE
			SYNTAX	INTEGER
			MAX-ACCESS	read-only
			STATUS	current
			::= { hmWanMbus80 62 }

hmWanMbus80Value1C		OBJECT-TYPE
			SYNTAX	INTEGER
			MAX-ACCESS	read-only
			STATUS	current
			::= { hmWanMbus80 63 }

hmWanMbus80VIF1D		OBJECT-TYPE
			SYNTAX	INTEGER
			MAX-ACCESS	read-only
			STATUS	current
			::= { hmWanMbus80 64 }

hmWanMbus80Value1D		OBJECT-TYPE
			SYNTAX	INTEGER
			MAX-ACCESS	read-only
			STATUS	current
			::= { hmWanMbus80 65 }

hmWanMbus80VIF1E		OBJECT-TYPE
			SYNTAX	INTEGER
			MAX-ACCESS	read-only
			STATUS	current
			::= { hmWanMbus80 66 }

hmWanMbus80Value1E		OBJECT-TYPE
			SYNTAX	INTEGER
			MAX-ACCESS	read-only
			STATUS	current
			::= { hmWanMbus80 67 }

hmWanMbus80VIF1F		OBJECT-TYPE
			SYNTAX	INTEGER
			MAX-ACCESS	read-only
			STATUS	current
			::= { hmWanMbus80 68 }

hmWanMbus80Value1F		OBJECT-TYPE
			SYNTAX	INTEGER
			MAX-ACCESS	read-only
			STATUS	current
			::= { hmWanMbus80 69 }

hmWanMbus80VIF20		OBJECT-TYPE
			SYNTAX	INTEGER
			MAX-ACCESS	read-only
			STATUS	current
			::= { hmWanMbus80 70 }

hmWanMbus80Value20		OBJECT-TYPE
			SYNTAX	INTEGER
			MAX-ACCESS	read-only
			STATUS	current
			::= { hmWanMbus80 71 }

hmWanMbus80VIF21		OBJECT-TYPE
			SYNTAX	INTEGER
			MAX-ACCESS	read-only
			STATUS	current
			::= { hmWanMbus80 72 }

hmWanMbus80Value21		OBJECT-TYPE
			SYNTAX	INTEGER
			MAX-ACCESS	read-only
			STATUS	current
			::= { hmWanMbus80 73 }

hmWanMbus80VIF22		OBJECT-TYPE
			SYNTAX	INTEGER
			MAX-ACCESS	read-only
			STATUS	current
			::= { hmWanMbus80 74 }

hmWanMbus80Value22		OBJECT-TYPE
			SYNTAX	INTEGER
			MAX-ACCESS	read-only
			STATUS	current
			::= { hmWanMbus80 75 }

hmWanMbus80VIF23		OBJECT-TYPE
			SYNTAX	INTEGER
			MAX-ACCESS	read-only
			STATUS	current
			::= { hmWanMbus80 76 }

hmWanMbus80Value23		OBJECT-TYPE
			SYNTAX	INTEGER
			MAX-ACCESS	read-only
			STATUS	current
			::= { hmWanMbus80 77 }

hmWanMbus80VIF24		OBJECT-TYPE
			SYNTAX	INTEGER
			MAX-ACCESS	read-only
			STATUS	current
			::= { hmWanMbus80 78 }

hmWanMbus80Value24		OBJECT-TYPE
			SYNTAX	INTEGER
			MAX-ACCESS	read-only
			STATUS	current
			::= { hmWanMbus80 79 }

hmWanMbus80VIF25		OBJECT-TYPE
			SYNTAX	INTEGER
			MAX-ACCESS	read-only
			STATUS	current
			::= { hmWanMbus80 80 }

hmWanMbus80Value25		OBJECT-TYPE
			SYNTAX	INTEGER
			MAX-ACCESS	read-only
			STATUS	current
			::= { hmWanMbus80 81 }

hmWanMbus80VIF26		OBJECT-TYPE
			SYNTAX	INTEGER
			MAX-ACCESS	read-only
			STATUS	current
			::= { hmWanMbus80 82 }

hmWanMbus80Value26		OBJECT-TYPE
			SYNTAX	INTEGER
			MAX-ACCESS	read-only
			STATUS	current
			::= { hmWanMbus80 83 }

hmWanMbus80VIF27		OBJECT-TYPE
			SYNTAX	INTEGER
			MAX-ACCESS	read-only
			STATUS	current
			::= { hmWanMbus80 84 }

hmWanMbus80Value27		OBJECT-TYPE
			SYNTAX	INTEGER
			MAX-ACCESS	read-only
			STATUS	current
			::= { hmWanMbus80 85 }

hmWanMbus80VIF28		OBJECT-TYPE
			SYNTAX	INTEGER
			MAX-ACCESS	read-only
			STATUS	current
			::= { hmWanMbus80 86 }

hmWanMbus80Value28		OBJECT-TYPE
			SYNTAX	INTEGER
			MAX-ACCESS	read-only
			STATUS	current
			::= { hmWanMbus80 87 }

hmWanMbus80VIF29		OBJECT-TYPE
			SYNTAX	INTEGER
			MAX-ACCESS	read-only
			STATUS	current
			::= { hmWanMbus80 88 }

hmWanMbus80Value29		OBJECT-TYPE
			SYNTAX	INTEGER
			MAX-ACCESS	read-only
			STATUS	current
			::= { hmWanMbus80 89 }

hmWanMbus80VIF2A		OBJECT-TYPE
			SYNTAX	INTEGER
			MAX-ACCESS	read-only
			STATUS	current
			::= { hmWanMbus80 90 }

hmWanMbus80Value2A		OBJECT-TYPE
			SYNTAX	INTEGER
			MAX-ACCESS	read-only
			STATUS	current
			::= { hmWanMbus80 91 }

hmWanMbus80VIF2B		OBJECT-TYPE
			SYNTAX	INTEGER
			MAX-ACCESS	read-only
			STATUS	current
			::= { hmWanMbus80 92 }

hmWanMbus80Value2B		OBJECT-TYPE
			SYNTAX	INTEGER
			MAX-ACCESS	read-only
			STATUS	current
			::= { hmWanMbus80 93 }

hmWanMbus80VIF2C		OBJECT-TYPE
			SYNTAX	INTEGER
			MAX-ACCESS	read-only
			STATUS	current
			::= { hmWanMbus80 94 }

hmWanMbus80Value2C		OBJECT-TYPE
			SYNTAX	INTEGER
			MAX-ACCESS	read-only
			STATUS	current
			::= { hmWanMbus80 95 }

hmWanMbus80VIF2D		OBJECT-TYPE
			SYNTAX	INTEGER
			MAX-ACCESS	read-only
			STATUS	current
			::= { hmWanMbus80 96 }

hmWanMbus80Value2D		OBJECT-TYPE
			SYNTAX	INTEGER
			MAX-ACCESS	read-only
			STATUS	current
			::= { hmWanMbus80 97 }

hmWanMbus80VIF2E		OBJECT-TYPE
			SYNTAX	INTEGER
			MAX-ACCESS	read-only
			STATUS	current
			::= { hmWanMbus80 98 }

hmWanMbus80Value2E		OBJECT-TYPE
			SYNTAX	INTEGER
			MAX-ACCESS	read-only
			STATUS	current
			::= { hmWanMbus80 99 }

hmWanMbus80VIF2F		OBJECT-TYPE
			SYNTAX	INTEGER
			MAX-ACCESS	read-only
			STATUS	current
			::= { hmWanMbus80 100 }

hmWanMbus80Value2F		OBJECT-TYPE
			SYNTAX	INTEGER
			MAX-ACCESS	read-only
			STATUS	current
			::= { hmWanMbus80 101 }

hmWanMbus81			OBJECT IDENTIFIER ::= { hmWanMbus 129 }

hmWanMbus81IdNumber		OBJECT-TYPE
			SYNTAX	Gauge32
			MAX-ACCESS	read-only
			STATUS	current
			::= { hmWanMbus81 1 }

hmWanMbus81Manufacturer	OBJECT-TYPE
			SYNTAX	Gauge32
			MAX-ACCESS	read-only
			STATUS	current
			::= { hmWanMbus81 2 }

hmWanMbus81Version		OBJECT-TYPE
			SYNTAX	Gauge32
			MAX-ACCESS	read-only
			STATUS	current
			::= { hmWanMbus81 3 }

hmWanMbus81Medium		OBJECT-TYPE
			SYNTAX	Gauge32
			MAX-ACCESS	read-only
			STATUS	current
			::= { hmWanMbus81 4 }

hmWanMbus81Status		OBJECT-TYPE
			SYNTAX	Gauge32
			MAX-ACCESS	read-only
			STATUS	current
			::= { hmWanMbus81 5 }

hmWanMbus81VIF00		OBJECT-TYPE
			SYNTAX	INTEGER
			MAX-ACCESS	read-only
			STATUS	current
			::= { hmWanMbus81 6 }

hmWanMbus81Value00		OBJECT-TYPE
			SYNTAX	INTEGER
			MAX-ACCESS	read-only
			STATUS	current
			::= { hmWanMbus81 7 }

hmWanMbus81VIF01		OBJECT-TYPE
			SYNTAX	INTEGER
			MAX-ACCESS	read-only
			STATUS	current
			::= { hmWanMbus81 8 }

hmWanMbus81Value01		OBJECT-TYPE
			SYNTAX	INTEGER
			MAX-ACCESS	read-only
			STATUS	current
			::= { hmWanMbus81 9 }

hmWanMbus81VIF02		OBJECT-TYPE
			SYNTAX	INTEGER
			MAX-ACCESS	read-only
			STATUS	current
			::= { hmWanMbus81 10 }

hmWanMbus81Value02		OBJECT-TYPE
			SYNTAX	INTEGER
			MAX-ACCESS	read-only
			STATUS	current
			::= { hmWanMbus81 11 }

hmWanMbus81VIF03		OBJECT-TYPE
			SYNTAX	INTEGER
			MAX-ACCESS	read-only
			STATUS	current
			::= { hmWanMbus81 12 }

hmWanMbus81Value03		OBJECT-TYPE
			SYNTAX	INTEGER
			MAX-ACCESS	read-only
			STATUS	current
			::= { hmWanMbus81 13 }

hmWanMbus81VIF04		OBJECT-TYPE
			SYNTAX	INTEGER
			MAX-ACCESS	read-only
			STATUS	current
			::= { hmWanMbus81 14 }

hmWanMbus81Value04		OBJECT-TYPE
			SYNTAX	INTEGER
			MAX-ACCESS	read-only
			STATUS	current
			::= { hmWanMbus81 15 }

hmWanMbus81VIF05		OBJECT-TYPE
			SYNTAX	INTEGER
			MAX-ACCESS	read-only
			STATUS	current
			::= { hmWanMbus81 16 }

hmWanMbus81Value05		OBJECT-TYPE
			SYNTAX	INTEGER
			MAX-ACCESS	read-only
			STATUS	current
			::= { hmWanMbus81 17 }

hmWanMbus81VIF06		OBJECT-TYPE
			SYNTAX	INTEGER
			MAX-ACCESS	read-only
			STATUS	current
			::= { hmWanMbus81 18 }

hmWanMbus81Value06		OBJECT-TYPE
			SYNTAX	INTEGER
			MAX-ACCESS	read-only
			STATUS	current
			::= { hmWanMbus81 19 }

hmWanMbus81VIF07		OBJECT-TYPE
			SYNTAX	INTEGER
			MAX-ACCESS	read-only
			STATUS	current
			::= { hmWanMbus81 20 }

hmWanMbus81Value07		OBJECT-TYPE
			SYNTAX	INTEGER
			MAX-ACCESS	read-only
			STATUS	current
			::= { hmWanMbus81 21 }

hmWanMbus81VIF08		OBJECT-TYPE
			SYNTAX	INTEGER
			MAX-ACCESS	read-only
			STATUS	current
			::= { hmWanMbus81 22 }

hmWanMbus81Value08		OBJECT-TYPE
			SYNTAX	INTEGER
			MAX-ACCESS	read-only
			STATUS	current
			::= { hmWanMbus81 23 }

hmWanMbus81VIF09		OBJECT-TYPE
			SYNTAX	INTEGER
			MAX-ACCESS	read-only
			STATUS	current
			::= { hmWanMbus81 24 }

hmWanMbus81Value09		OBJECT-TYPE
			SYNTAX	INTEGER
			MAX-ACCESS	read-only
			STATUS	current
			::= { hmWanMbus81 25 }

hmWanMbus81VIF0A		OBJECT-TYPE
			SYNTAX	INTEGER
			MAX-ACCESS	read-only
			STATUS	current
			::= { hmWanMbus81 26 }

hmWanMbus81Value0A		OBJECT-TYPE
			SYNTAX	INTEGER
			MAX-ACCESS	read-only
			STATUS	current
			::= { hmWanMbus81 27 }

hmWanMbus81VIF0B		OBJECT-TYPE
			SYNTAX	INTEGER
			MAX-ACCESS	read-only
			STATUS	current
			::= { hmWanMbus81 28 }

hmWanMbus81Value0B		OBJECT-TYPE
			SYNTAX	INTEGER
			MAX-ACCESS	read-only
			STATUS	current
			::= { hmWanMbus81 29 }

hmWanMbus81VIF0C		OBJECT-TYPE
			SYNTAX	INTEGER
			MAX-ACCESS	read-only
			STATUS	current
			::= { hmWanMbus81 30 }

hmWanMbus81Value0C		OBJECT-TYPE
			SYNTAX	INTEGER
			MAX-ACCESS	read-only
			STATUS	current
			::= { hmWanMbus81 31 }

hmWanMbus81VIF0D		OBJECT-TYPE
			SYNTAX	INTEGER
			MAX-ACCESS	read-only
			STATUS	current
			::= { hmWanMbus81 32 }

hmWanMbus81Value0D		OBJECT-TYPE
			SYNTAX	INTEGER
			MAX-ACCESS	read-only
			STATUS	current
			::= { hmWanMbus81 33 }

hmWanMbus81VIF0E		OBJECT-TYPE
			SYNTAX	INTEGER
			MAX-ACCESS	read-only
			STATUS	current
			::= { hmWanMbus81 34 }

hmWanMbus81Value0E		OBJECT-TYPE
			SYNTAX	INTEGER
			MAX-ACCESS	read-only
			STATUS	current
			::= { hmWanMbus81 35 }

hmWanMbus81VIF0F		OBJECT-TYPE
			SYNTAX	INTEGER
			MAX-ACCESS	read-only
			STATUS	current
			::= { hmWanMbus81 36 }

hmWanMbus81Value0F		OBJECT-TYPE
			SYNTAX	INTEGER
			MAX-ACCESS	read-only
			STATUS	current
			::= { hmWanMbus81 37 }

hmWanMbus81VIF10		OBJECT-TYPE
			SYNTAX	INTEGER
			MAX-ACCESS	read-only
			STATUS	current
			::= { hmWanMbus81 38 }

hmWanMbus81Value10		OBJECT-TYPE
			SYNTAX	INTEGER
			MAX-ACCESS	read-only
			STATUS	current
			::= { hmWanMbus81 39 }

hmWanMbus81VIF11		OBJECT-TYPE
			SYNTAX	INTEGER
			MAX-ACCESS	read-only
			STATUS	current
			::= { hmWanMbus81 40 }

hmWanMbus81Value11		OBJECT-TYPE
			SYNTAX	INTEGER
			MAX-ACCESS	read-only
			STATUS	current
			::= { hmWanMbus81 41 }

hmWanMbus81VIF12		OBJECT-TYPE
			SYNTAX	INTEGER
			MAX-ACCESS	read-only
			STATUS	current
			::= { hmWanMbus81 42 }

hmWanMbus81Value12		OBJECT-TYPE
			SYNTAX	INTEGER
			MAX-ACCESS	read-only
			STATUS	current
			::= { hmWanMbus81 43 }

hmWanMbus81VIF13		OBJECT-TYPE
			SYNTAX	INTEGER
			MAX-ACCESS	read-only
			STATUS	current
			::= { hmWanMbus81 44 }

hmWanMbus81Value13		OBJECT-TYPE
			SYNTAX	INTEGER
			MAX-ACCESS	read-only
			STATUS	current
			::= { hmWanMbus81 45 }

hmWanMbus81VIF14		OBJECT-TYPE
			SYNTAX	INTEGER
			MAX-ACCESS	read-only
			STATUS	current
			::= { hmWanMbus81 46 }

hmWanMbus81Value14		OBJECT-TYPE
			SYNTAX	INTEGER
			MAX-ACCESS	read-only
			STATUS	current
			::= { hmWanMbus81 47 }

hmWanMbus81VIF15		OBJECT-TYPE
			SYNTAX	INTEGER
			MAX-ACCESS	read-only
			STATUS	current
			::= { hmWanMbus81 48 }

hmWanMbus81Value15		OBJECT-TYPE
			SYNTAX	INTEGER
			MAX-ACCESS	read-only
			STATUS	current
			::= { hmWanMbus81 49 }

hmWanMbus81VIF16		OBJECT-TYPE
			SYNTAX	INTEGER
			MAX-ACCESS	read-only
			STATUS	current
			::= { hmWanMbus81 50 }

hmWanMbus81Value16		OBJECT-TYPE
			SYNTAX	INTEGER
			MAX-ACCESS	read-only
			STATUS	current
			::= { hmWanMbus81 51 }

hmWanMbus81VIF17		OBJECT-TYPE
			SYNTAX	INTEGER
			MAX-ACCESS	read-only
			STATUS	current
			::= { hmWanMbus81 52 }

hmWanMbus81Value17		OBJECT-TYPE
			SYNTAX	INTEGER
			MAX-ACCESS	read-only
			STATUS	current
			::= { hmWanMbus81 53 }

hmWanMbus81VIF18		OBJECT-TYPE
			SYNTAX	INTEGER
			MAX-ACCESS	read-only
			STATUS	current
			::= { hmWanMbus81 54 }

hmWanMbus81Value18		OBJECT-TYPE
			SYNTAX	INTEGER
			MAX-ACCESS	read-only
			STATUS	current
			::= { hmWanMbus81 55 }

hmWanMbus81VIF19		OBJECT-TYPE
			SYNTAX	INTEGER
			MAX-ACCESS	read-only
			STATUS	current
			::= { hmWanMbus81 56 }

hmWanMbus81Value19		OBJECT-TYPE
			SYNTAX	INTEGER
			MAX-ACCESS	read-only
			STATUS	current
			::= { hmWanMbus81 57 }

hmWanMbus81VIF1A		OBJECT-TYPE
			SYNTAX	INTEGER
			MAX-ACCESS	read-only
			STATUS	current
			::= { hmWanMbus81 58 }

hmWanMbus81Value1A		OBJECT-TYPE
			SYNTAX	INTEGER
			MAX-ACCESS	read-only
			STATUS	current
			::= { hmWanMbus81 59 }

hmWanMbus81VIF1B		OBJECT-TYPE
			SYNTAX	INTEGER
			MAX-ACCESS	read-only
			STATUS	current
			::= { hmWanMbus81 60 }

hmWanMbus81Value1B		OBJECT-TYPE
			SYNTAX	INTEGER
			MAX-ACCESS	read-only
			STATUS	current
			::= { hmWanMbus81 61 }

hmWanMbus81VIF1C		OBJECT-TYPE
			SYNTAX	INTEGER
			MAX-ACCESS	read-only
			STATUS	current
			::= { hmWanMbus81 62 }

hmWanMbus81Value1C		OBJECT-TYPE
			SYNTAX	INTEGER
			MAX-ACCESS	read-only
			STATUS	current
			::= { hmWanMbus81 63 }

hmWanMbus81VIF1D		OBJECT-TYPE
			SYNTAX	INTEGER
			MAX-ACCESS	read-only
			STATUS	current
			::= { hmWanMbus81 64 }

hmWanMbus81Value1D		OBJECT-TYPE
			SYNTAX	INTEGER
			MAX-ACCESS	read-only
			STATUS	current
			::= { hmWanMbus81 65 }

hmWanMbus81VIF1E		OBJECT-TYPE
			SYNTAX	INTEGER
			MAX-ACCESS	read-only
			STATUS	current
			::= { hmWanMbus81 66 }

hmWanMbus81Value1E		OBJECT-TYPE
			SYNTAX	INTEGER
			MAX-ACCESS	read-only
			STATUS	current
			::= { hmWanMbus81 67 }

hmWanMbus81VIF1F		OBJECT-TYPE
			SYNTAX	INTEGER
			MAX-ACCESS	read-only
			STATUS	current
			::= { hmWanMbus81 68 }

hmWanMbus81Value1F		OBJECT-TYPE
			SYNTAX	INTEGER
			MAX-ACCESS	read-only
			STATUS	current
			::= { hmWanMbus81 69 }

hmWanMbus81VIF20		OBJECT-TYPE
			SYNTAX	INTEGER
			MAX-ACCESS	read-only
			STATUS	current
			::= { hmWanMbus81 70 }

hmWanMbus81Value20		OBJECT-TYPE
			SYNTAX	INTEGER
			MAX-ACCESS	read-only
			STATUS	current
			::= { hmWanMbus81 71 }

hmWanMbus81VIF21		OBJECT-TYPE
			SYNTAX	INTEGER
			MAX-ACCESS	read-only
			STATUS	current
			::= { hmWanMbus81 72 }

hmWanMbus81Value21		OBJECT-TYPE
			SYNTAX	INTEGER
			MAX-ACCESS	read-only
			STATUS	current
			::= { hmWanMbus81 73 }

hmWanMbus81VIF22		OBJECT-TYPE
			SYNTAX	INTEGER
			MAX-ACCESS	read-only
			STATUS	current
			::= { hmWanMbus81 74 }

hmWanMbus81Value22		OBJECT-TYPE
			SYNTAX	INTEGER
			MAX-ACCESS	read-only
			STATUS	current
			::= { hmWanMbus81 75 }

hmWanMbus81VIF23		OBJECT-TYPE
			SYNTAX	INTEGER
			MAX-ACCESS	read-only
			STATUS	current
			::= { hmWanMbus81 76 }

hmWanMbus81Value23		OBJECT-TYPE
			SYNTAX	INTEGER
			MAX-ACCESS	read-only
			STATUS	current
			::= { hmWanMbus81 77 }

hmWanMbus81VIF24		OBJECT-TYPE
			SYNTAX	INTEGER
			MAX-ACCESS	read-only
			STATUS	current
			::= { hmWanMbus81 78 }

hmWanMbus81Value24		OBJECT-TYPE
			SYNTAX	INTEGER
			MAX-ACCESS	read-only
			STATUS	current
			::= { hmWanMbus81 79 }

hmWanMbus81VIF25		OBJECT-TYPE
			SYNTAX	INTEGER
			MAX-ACCESS	read-only
			STATUS	current
			::= { hmWanMbus81 80 }

hmWanMbus81Value25		OBJECT-TYPE
			SYNTAX	INTEGER
			MAX-ACCESS	read-only
			STATUS	current
			::= { hmWanMbus81 81 }

hmWanMbus81VIF26		OBJECT-TYPE
			SYNTAX	INTEGER
			MAX-ACCESS	read-only
			STATUS	current
			::= { hmWanMbus81 82 }

hmWanMbus81Value26		OBJECT-TYPE
			SYNTAX	INTEGER
			MAX-ACCESS	read-only
			STATUS	current
			::= { hmWanMbus81 83 }

hmWanMbus81VIF27		OBJECT-TYPE
			SYNTAX	INTEGER
			MAX-ACCESS	read-only
			STATUS	current
			::= { hmWanMbus81 84 }

hmWanMbus81Value27		OBJECT-TYPE
			SYNTAX	INTEGER
			MAX-ACCESS	read-only
			STATUS	current
			::= { hmWanMbus81 85 }

hmWanMbus81VIF28		OBJECT-TYPE
			SYNTAX	INTEGER
			MAX-ACCESS	read-only
			STATUS	current
			::= { hmWanMbus81 86 }

hmWanMbus81Value28		OBJECT-TYPE
			SYNTAX	INTEGER
			MAX-ACCESS	read-only
			STATUS	current
			::= { hmWanMbus81 87 }

hmWanMbus81VIF29		OBJECT-TYPE
			SYNTAX	INTEGER
			MAX-ACCESS	read-only
			STATUS	current
			::= { hmWanMbus81 88 }

hmWanMbus81Value29		OBJECT-TYPE
			SYNTAX	INTEGER
			MAX-ACCESS	read-only
			STATUS	current
			::= { hmWanMbus81 89 }

hmWanMbus81VIF2A		OBJECT-TYPE
			SYNTAX	INTEGER
			MAX-ACCESS	read-only
			STATUS	current
			::= { hmWanMbus81 90 }

hmWanMbus81Value2A		OBJECT-TYPE
			SYNTAX	INTEGER
			MAX-ACCESS	read-only
			STATUS	current
			::= { hmWanMbus81 91 }

hmWanMbus81VIF2B		OBJECT-TYPE
			SYNTAX	INTEGER
			MAX-ACCESS	read-only
			STATUS	current
			::= { hmWanMbus81 92 }

hmWanMbus81Value2B		OBJECT-TYPE
			SYNTAX	INTEGER
			MAX-ACCESS	read-only
			STATUS	current
			::= { hmWanMbus81 93 }

hmWanMbus81VIF2C		OBJECT-TYPE
			SYNTAX	INTEGER
			MAX-ACCESS	read-only
			STATUS	current
			::= { hmWanMbus81 94 }

hmWanMbus81Value2C		OBJECT-TYPE
			SYNTAX	INTEGER
			MAX-ACCESS	read-only
			STATUS	current
			::= { hmWanMbus81 95 }

hmWanMbus81VIF2D		OBJECT-TYPE
			SYNTAX	INTEGER
			MAX-ACCESS	read-only
			STATUS	current
			::= { hmWanMbus81 96 }

hmWanMbus81Value2D		OBJECT-TYPE
			SYNTAX	INTEGER
			MAX-ACCESS	read-only
			STATUS	current
			::= { hmWanMbus81 97 }

hmWanMbus81VIF2E		OBJECT-TYPE
			SYNTAX	INTEGER
			MAX-ACCESS	read-only
			STATUS	current
			::= { hmWanMbus81 98 }

hmWanMbus81Value2E		OBJECT-TYPE
			SYNTAX	INTEGER
			MAX-ACCESS	read-only
			STATUS	current
			::= { hmWanMbus81 99 }

hmWanMbus81VIF2F		OBJECT-TYPE
			SYNTAX	INTEGER
			MAX-ACCESS	read-only
			STATUS	current
			::= { hmWanMbus81 100 }

hmWanMbus81Value2F		OBJECT-TYPE
			SYNTAX	INTEGER
			MAX-ACCESS	read-only
			STATUS	current
			::= { hmWanMbus81 101 }

hmWanMbus82			OBJECT IDENTIFIER ::= { hmWanMbus 130 }

hmWanMbus82IdNumber		OBJECT-TYPE
			SYNTAX	Gauge32
			MAX-ACCESS	read-only
			STATUS	current
			::= { hmWanMbus82 1 }

hmWanMbus82Manufacturer	OBJECT-TYPE
			SYNTAX	Gauge32
			MAX-ACCESS	read-only
			STATUS	current
			::= { hmWanMbus82 2 }

hmWanMbus82Version		OBJECT-TYPE
			SYNTAX	Gauge32
			MAX-ACCESS	read-only
			STATUS	current
			::= { hmWanMbus82 3 }

hmWanMbus82Medium		OBJECT-TYPE
			SYNTAX	Gauge32
			MAX-ACCESS	read-only
			STATUS	current
			::= { hmWanMbus82 4 }

hmWanMbus82Status		OBJECT-TYPE
			SYNTAX	Gauge32
			MAX-ACCESS	read-only
			STATUS	current
			::= { hmWanMbus82 5 }

hmWanMbus82VIF00		OBJECT-TYPE
			SYNTAX	INTEGER
			MAX-ACCESS	read-only
			STATUS	current
			::= { hmWanMbus82 6 }

hmWanMbus82Value00		OBJECT-TYPE
			SYNTAX	INTEGER
			MAX-ACCESS	read-only
			STATUS	current
			::= { hmWanMbus82 7 }

hmWanMbus82VIF01		OBJECT-TYPE
			SYNTAX	INTEGER
			MAX-ACCESS	read-only
			STATUS	current
			::= { hmWanMbus82 8 }

hmWanMbus82Value01		OBJECT-TYPE
			SYNTAX	INTEGER
			MAX-ACCESS	read-only
			STATUS	current
			::= { hmWanMbus82 9 }

hmWanMbus82VIF02		OBJECT-TYPE
			SYNTAX	INTEGER
			MAX-ACCESS	read-only
			STATUS	current
			::= { hmWanMbus82 10 }

hmWanMbus82Value02		OBJECT-TYPE
			SYNTAX	INTEGER
			MAX-ACCESS	read-only
			STATUS	current
			::= { hmWanMbus82 11 }

hmWanMbus82VIF03		OBJECT-TYPE
			SYNTAX	INTEGER
			MAX-ACCESS	read-only
			STATUS	current
			::= { hmWanMbus82 12 }

hmWanMbus82Value03		OBJECT-TYPE
			SYNTAX	INTEGER
			MAX-ACCESS	read-only
			STATUS	current
			::= { hmWanMbus82 13 }

hmWanMbus82VIF04		OBJECT-TYPE
			SYNTAX	INTEGER
			MAX-ACCESS	read-only
			STATUS	current
			::= { hmWanMbus82 14 }

hmWanMbus82Value04		OBJECT-TYPE
			SYNTAX	INTEGER
			MAX-ACCESS	read-only
			STATUS	current
			::= { hmWanMbus82 15 }

hmWanMbus82VIF05		OBJECT-TYPE
			SYNTAX	INTEGER
			MAX-ACCESS	read-only
			STATUS	current
			::= { hmWanMbus82 16 }

hmWanMbus82Value05		OBJECT-TYPE
			SYNTAX	INTEGER
			MAX-ACCESS	read-only
			STATUS	current
			::= { hmWanMbus82 17 }

hmWanMbus82VIF06		OBJECT-TYPE
			SYNTAX	INTEGER
			MAX-ACCESS	read-only
			STATUS	current
			::= { hmWanMbus82 18 }

hmWanMbus82Value06		OBJECT-TYPE
			SYNTAX	INTEGER
			MAX-ACCESS	read-only
			STATUS	current
			::= { hmWanMbus82 19 }

hmWanMbus82VIF07		OBJECT-TYPE
			SYNTAX	INTEGER
			MAX-ACCESS	read-only
			STATUS	current
			::= { hmWanMbus82 20 }

hmWanMbus82Value07		OBJECT-TYPE
			SYNTAX	INTEGER
			MAX-ACCESS	read-only
			STATUS	current
			::= { hmWanMbus82 21 }

hmWanMbus82VIF08		OBJECT-TYPE
			SYNTAX	INTEGER
			MAX-ACCESS	read-only
			STATUS	current
			::= { hmWanMbus82 22 }

hmWanMbus82Value08		OBJECT-TYPE
			SYNTAX	INTEGER
			MAX-ACCESS	read-only
			STATUS	current
			::= { hmWanMbus82 23 }

hmWanMbus82VIF09		OBJECT-TYPE
			SYNTAX	INTEGER
			MAX-ACCESS	read-only
			STATUS	current
			::= { hmWanMbus82 24 }

hmWanMbus82Value09		OBJECT-TYPE
			SYNTAX	INTEGER
			MAX-ACCESS	read-only
			STATUS	current
			::= { hmWanMbus82 25 }

hmWanMbus82VIF0A		OBJECT-TYPE
			SYNTAX	INTEGER
			MAX-ACCESS	read-only
			STATUS	current
			::= { hmWanMbus82 26 }

hmWanMbus82Value0A		OBJECT-TYPE
			SYNTAX	INTEGER
			MAX-ACCESS	read-only
			STATUS	current
			::= { hmWanMbus82 27 }

hmWanMbus82VIF0B		OBJECT-TYPE
			SYNTAX	INTEGER
			MAX-ACCESS	read-only
			STATUS	current
			::= { hmWanMbus82 28 }

hmWanMbus82Value0B		OBJECT-TYPE
			SYNTAX	INTEGER
			MAX-ACCESS	read-only
			STATUS	current
			::= { hmWanMbus82 29 }

hmWanMbus82VIF0C		OBJECT-TYPE
			SYNTAX	INTEGER
			MAX-ACCESS	read-only
			STATUS	current
			::= { hmWanMbus82 30 }

hmWanMbus82Value0C		OBJECT-TYPE
			SYNTAX	INTEGER
			MAX-ACCESS	read-only
			STATUS	current
			::= { hmWanMbus82 31 }

hmWanMbus82VIF0D		OBJECT-TYPE
			SYNTAX	INTEGER
			MAX-ACCESS	read-only
			STATUS	current
			::= { hmWanMbus82 32 }

hmWanMbus82Value0D		OBJECT-TYPE
			SYNTAX	INTEGER
			MAX-ACCESS	read-only
			STATUS	current
			::= { hmWanMbus82 33 }

hmWanMbus82VIF0E		OBJECT-TYPE
			SYNTAX	INTEGER
			MAX-ACCESS	read-only
			STATUS	current
			::= { hmWanMbus82 34 }

hmWanMbus82Value0E		OBJECT-TYPE
			SYNTAX	INTEGER
			MAX-ACCESS	read-only
			STATUS	current
			::= { hmWanMbus82 35 }

hmWanMbus82VIF0F		OBJECT-TYPE
			SYNTAX	INTEGER
			MAX-ACCESS	read-only
			STATUS	current
			::= { hmWanMbus82 36 }

hmWanMbus82Value0F		OBJECT-TYPE
			SYNTAX	INTEGER
			MAX-ACCESS	read-only
			STATUS	current
			::= { hmWanMbus82 37 }

hmWanMbus82VIF10		OBJECT-TYPE
			SYNTAX	INTEGER
			MAX-ACCESS	read-only
			STATUS	current
			::= { hmWanMbus82 38 }

hmWanMbus82Value10		OBJECT-TYPE
			SYNTAX	INTEGER
			MAX-ACCESS	read-only
			STATUS	current
			::= { hmWanMbus82 39 }

hmWanMbus82VIF11		OBJECT-TYPE
			SYNTAX	INTEGER
			MAX-ACCESS	read-only
			STATUS	current
			::= { hmWanMbus82 40 }

hmWanMbus82Value11		OBJECT-TYPE
			SYNTAX	INTEGER
			MAX-ACCESS	read-only
			STATUS	current
			::= { hmWanMbus82 41 }

hmWanMbus82VIF12		OBJECT-TYPE
			SYNTAX	INTEGER
			MAX-ACCESS	read-only
			STATUS	current
			::= { hmWanMbus82 42 }

hmWanMbus82Value12		OBJECT-TYPE
			SYNTAX	INTEGER
			MAX-ACCESS	read-only
			STATUS	current
			::= { hmWanMbus82 43 }

hmWanMbus82VIF13		OBJECT-TYPE
			SYNTAX	INTEGER
			MAX-ACCESS	read-only
			STATUS	current
			::= { hmWanMbus82 44 }

hmWanMbus82Value13		OBJECT-TYPE
			SYNTAX	INTEGER
			MAX-ACCESS	read-only
			STATUS	current
			::= { hmWanMbus82 45 }

hmWanMbus82VIF14		OBJECT-TYPE
			SYNTAX	INTEGER
			MAX-ACCESS	read-only
			STATUS	current
			::= { hmWanMbus82 46 }

hmWanMbus82Value14		OBJECT-TYPE
			SYNTAX	INTEGER
			MAX-ACCESS	read-only
			STATUS	current
			::= { hmWanMbus82 47 }

hmWanMbus82VIF15		OBJECT-TYPE
			SYNTAX	INTEGER
			MAX-ACCESS	read-only
			STATUS	current
			::= { hmWanMbus82 48 }

hmWanMbus82Value15		OBJECT-TYPE
			SYNTAX	INTEGER
			MAX-ACCESS	read-only
			STATUS	current
			::= { hmWanMbus82 49 }

hmWanMbus82VIF16		OBJECT-TYPE
			SYNTAX	INTEGER
			MAX-ACCESS	read-only
			STATUS	current
			::= { hmWanMbus82 50 }

hmWanMbus82Value16		OBJECT-TYPE
			SYNTAX	INTEGER
			MAX-ACCESS	read-only
			STATUS	current
			::= { hmWanMbus82 51 }

hmWanMbus82VIF17		OBJECT-TYPE
			SYNTAX	INTEGER
			MAX-ACCESS	read-only
			STATUS	current
			::= { hmWanMbus82 52 }

hmWanMbus82Value17		OBJECT-TYPE
			SYNTAX	INTEGER
			MAX-ACCESS	read-only
			STATUS	current
			::= { hmWanMbus82 53 }

hmWanMbus82VIF18		OBJECT-TYPE
			SYNTAX	INTEGER
			MAX-ACCESS	read-only
			STATUS	current
			::= { hmWanMbus82 54 }

hmWanMbus82Value18		OBJECT-TYPE
			SYNTAX	INTEGER
			MAX-ACCESS	read-only
			STATUS	current
			::= { hmWanMbus82 55 }

hmWanMbus82VIF19		OBJECT-TYPE
			SYNTAX	INTEGER
			MAX-ACCESS	read-only
			STATUS	current
			::= { hmWanMbus82 56 }

hmWanMbus82Value19		OBJECT-TYPE
			SYNTAX	INTEGER
			MAX-ACCESS	read-only
			STATUS	current
			::= { hmWanMbus82 57 }

hmWanMbus82VIF1A		OBJECT-TYPE
			SYNTAX	INTEGER
			MAX-ACCESS	read-only
			STATUS	current
			::= { hmWanMbus82 58 }

hmWanMbus82Value1A		OBJECT-TYPE
			SYNTAX	INTEGER
			MAX-ACCESS	read-only
			STATUS	current
			::= { hmWanMbus82 59 }

hmWanMbus82VIF1B		OBJECT-TYPE
			SYNTAX	INTEGER
			MAX-ACCESS	read-only
			STATUS	current
			::= { hmWanMbus82 60 }

hmWanMbus82Value1B		OBJECT-TYPE
			SYNTAX	INTEGER
			MAX-ACCESS	read-only
			STATUS	current
			::= { hmWanMbus82 61 }

hmWanMbus82VIF1C		OBJECT-TYPE
			SYNTAX	INTEGER
			MAX-ACCESS	read-only
			STATUS	current
			::= { hmWanMbus82 62 }

hmWanMbus82Value1C		OBJECT-TYPE
			SYNTAX	INTEGER
			MAX-ACCESS	read-only
			STATUS	current
			::= { hmWanMbus82 63 }

hmWanMbus82VIF1D		OBJECT-TYPE
			SYNTAX	INTEGER
			MAX-ACCESS	read-only
			STATUS	current
			::= { hmWanMbus82 64 }

hmWanMbus82Value1D		OBJECT-TYPE
			SYNTAX	INTEGER
			MAX-ACCESS	read-only
			STATUS	current
			::= { hmWanMbus82 65 }

hmWanMbus82VIF1E		OBJECT-TYPE
			SYNTAX	INTEGER
			MAX-ACCESS	read-only
			STATUS	current
			::= { hmWanMbus82 66 }

hmWanMbus82Value1E		OBJECT-TYPE
			SYNTAX	INTEGER
			MAX-ACCESS	read-only
			STATUS	current
			::= { hmWanMbus82 67 }

hmWanMbus82VIF1F		OBJECT-TYPE
			SYNTAX	INTEGER
			MAX-ACCESS	read-only
			STATUS	current
			::= { hmWanMbus82 68 }

hmWanMbus82Value1F		OBJECT-TYPE
			SYNTAX	INTEGER
			MAX-ACCESS	read-only
			STATUS	current
			::= { hmWanMbus82 69 }

hmWanMbus82VIF20		OBJECT-TYPE
			SYNTAX	INTEGER
			MAX-ACCESS	read-only
			STATUS	current
			::= { hmWanMbus82 70 }

hmWanMbus82Value20		OBJECT-TYPE
			SYNTAX	INTEGER
			MAX-ACCESS	read-only
			STATUS	current
			::= { hmWanMbus82 71 }

hmWanMbus82VIF21		OBJECT-TYPE
			SYNTAX	INTEGER
			MAX-ACCESS	read-only
			STATUS	current
			::= { hmWanMbus82 72 }

hmWanMbus82Value21		OBJECT-TYPE
			SYNTAX	INTEGER
			MAX-ACCESS	read-only
			STATUS	current
			::= { hmWanMbus82 73 }

hmWanMbus82VIF22		OBJECT-TYPE
			SYNTAX	INTEGER
			MAX-ACCESS	read-only
			STATUS	current
			::= { hmWanMbus82 74 }

hmWanMbus82Value22		OBJECT-TYPE
			SYNTAX	INTEGER
			MAX-ACCESS	read-only
			STATUS	current
			::= { hmWanMbus82 75 }

hmWanMbus82VIF23		OBJECT-TYPE
			SYNTAX	INTEGER
			MAX-ACCESS	read-only
			STATUS	current
			::= { hmWanMbus82 76 }

hmWanMbus82Value23		OBJECT-TYPE
			SYNTAX	INTEGER
			MAX-ACCESS	read-only
			STATUS	current
			::= { hmWanMbus82 77 }

hmWanMbus82VIF24		OBJECT-TYPE
			SYNTAX	INTEGER
			MAX-ACCESS	read-only
			STATUS	current
			::= { hmWanMbus82 78 }

hmWanMbus82Value24		OBJECT-TYPE
			SYNTAX	INTEGER
			MAX-ACCESS	read-only
			STATUS	current
			::= { hmWanMbus82 79 }

hmWanMbus82VIF25		OBJECT-TYPE
			SYNTAX	INTEGER
			MAX-ACCESS	read-only
			STATUS	current
			::= { hmWanMbus82 80 }

hmWanMbus82Value25		OBJECT-TYPE
			SYNTAX	INTEGER
			MAX-ACCESS	read-only
			STATUS	current
			::= { hmWanMbus82 81 }

hmWanMbus82VIF26		OBJECT-TYPE
			SYNTAX	INTEGER
			MAX-ACCESS	read-only
			STATUS	current
			::= { hmWanMbus82 82 }

hmWanMbus82Value26		OBJECT-TYPE
			SYNTAX	INTEGER
			MAX-ACCESS	read-only
			STATUS	current
			::= { hmWanMbus82 83 }

hmWanMbus82VIF27		OBJECT-TYPE
			SYNTAX	INTEGER
			MAX-ACCESS	read-only
			STATUS	current
			::= { hmWanMbus82 84 }

hmWanMbus82Value27		OBJECT-TYPE
			SYNTAX	INTEGER
			MAX-ACCESS	read-only
			STATUS	current
			::= { hmWanMbus82 85 }

hmWanMbus82VIF28		OBJECT-TYPE
			SYNTAX	INTEGER
			MAX-ACCESS	read-only
			STATUS	current
			::= { hmWanMbus82 86 }

hmWanMbus82Value28		OBJECT-TYPE
			SYNTAX	INTEGER
			MAX-ACCESS	read-only
			STATUS	current
			::= { hmWanMbus82 87 }

hmWanMbus82VIF29		OBJECT-TYPE
			SYNTAX	INTEGER
			MAX-ACCESS	read-only
			STATUS	current
			::= { hmWanMbus82 88 }

hmWanMbus82Value29		OBJECT-TYPE
			SYNTAX	INTEGER
			MAX-ACCESS	read-only
			STATUS	current
			::= { hmWanMbus82 89 }

hmWanMbus82VIF2A		OBJECT-TYPE
			SYNTAX	INTEGER
			MAX-ACCESS	read-only
			STATUS	current
			::= { hmWanMbus82 90 }

hmWanMbus82Value2A		OBJECT-TYPE
			SYNTAX	INTEGER
			MAX-ACCESS	read-only
			STATUS	current
			::= { hmWanMbus82 91 }

hmWanMbus82VIF2B		OBJECT-TYPE
			SYNTAX	INTEGER
			MAX-ACCESS	read-only
			STATUS	current
			::= { hmWanMbus82 92 }

hmWanMbus82Value2B		OBJECT-TYPE
			SYNTAX	INTEGER
			MAX-ACCESS	read-only
			STATUS	current
			::= { hmWanMbus82 93 }

hmWanMbus82VIF2C		OBJECT-TYPE
			SYNTAX	INTEGER
			MAX-ACCESS	read-only
			STATUS	current
			::= { hmWanMbus82 94 }

hmWanMbus82Value2C		OBJECT-TYPE
			SYNTAX	INTEGER
			MAX-ACCESS	read-only
			STATUS	current
			::= { hmWanMbus82 95 }

hmWanMbus82VIF2D		OBJECT-TYPE
			SYNTAX	INTEGER
			MAX-ACCESS	read-only
			STATUS	current
			::= { hmWanMbus82 96 }

hmWanMbus82Value2D		OBJECT-TYPE
			SYNTAX	INTEGER
			MAX-ACCESS	read-only
			STATUS	current
			::= { hmWanMbus82 97 }

hmWanMbus82VIF2E		OBJECT-TYPE
			SYNTAX	INTEGER
			MAX-ACCESS	read-only
			STATUS	current
			::= { hmWanMbus82 98 }

hmWanMbus82Value2E		OBJECT-TYPE
			SYNTAX	INTEGER
			MAX-ACCESS	read-only
			STATUS	current
			::= { hmWanMbus82 99 }

hmWanMbus82VIF2F		OBJECT-TYPE
			SYNTAX	INTEGER
			MAX-ACCESS	read-only
			STATUS	current
			::= { hmWanMbus82 100 }

hmWanMbus82Value2F		OBJECT-TYPE
			SYNTAX	INTEGER
			MAX-ACCESS	read-only
			STATUS	current
			::= { hmWanMbus82 101 }

hmWanMbus83			OBJECT IDENTIFIER ::= { hmWanMbus 131 }

hmWanMbus83IdNumber		OBJECT-TYPE
			SYNTAX	Gauge32
			MAX-ACCESS	read-only
			STATUS	current
			::= { hmWanMbus83 1 }

hmWanMbus83Manufacturer	OBJECT-TYPE
			SYNTAX	Gauge32
			MAX-ACCESS	read-only
			STATUS	current
			::= { hmWanMbus83 2 }

hmWanMbus83Version		OBJECT-TYPE
			SYNTAX	Gauge32
			MAX-ACCESS	read-only
			STATUS	current
			::= { hmWanMbus83 3 }

hmWanMbus83Medium		OBJECT-TYPE
			SYNTAX	Gauge32
			MAX-ACCESS	read-only
			STATUS	current
			::= { hmWanMbus83 4 }

hmWanMbus83Status		OBJECT-TYPE
			SYNTAX	Gauge32
			MAX-ACCESS	read-only
			STATUS	current
			::= { hmWanMbus83 5 }

hmWanMbus83VIF00		OBJECT-TYPE
			SYNTAX	INTEGER
			MAX-ACCESS	read-only
			STATUS	current
			::= { hmWanMbus83 6 }

hmWanMbus83Value00		OBJECT-TYPE
			SYNTAX	INTEGER
			MAX-ACCESS	read-only
			STATUS	current
			::= { hmWanMbus83 7 }

hmWanMbus83VIF01		OBJECT-TYPE
			SYNTAX	INTEGER
			MAX-ACCESS	read-only
			STATUS	current
			::= { hmWanMbus83 8 }

hmWanMbus83Value01		OBJECT-TYPE
			SYNTAX	INTEGER
			MAX-ACCESS	read-only
			STATUS	current
			::= { hmWanMbus83 9 }

hmWanMbus83VIF02		OBJECT-TYPE
			SYNTAX	INTEGER
			MAX-ACCESS	read-only
			STATUS	current
			::= { hmWanMbus83 10 }

hmWanMbus83Value02		OBJECT-TYPE
			SYNTAX	INTEGER
			MAX-ACCESS	read-only
			STATUS	current
			::= { hmWanMbus83 11 }

hmWanMbus83VIF03		OBJECT-TYPE
			SYNTAX	INTEGER
			MAX-ACCESS	read-only
			STATUS	current
			::= { hmWanMbus83 12 }

hmWanMbus83Value03		OBJECT-TYPE
			SYNTAX	INTEGER
			MAX-ACCESS	read-only
			STATUS	current
			::= { hmWanMbus83 13 }

hmWanMbus83VIF04		OBJECT-TYPE
			SYNTAX	INTEGER
			MAX-ACCESS	read-only
			STATUS	current
			::= { hmWanMbus83 14 }

hmWanMbus83Value04		OBJECT-TYPE
			SYNTAX	INTEGER
			MAX-ACCESS	read-only
			STATUS	current
			::= { hmWanMbus83 15 }

hmWanMbus83VIF05		OBJECT-TYPE
			SYNTAX	INTEGER
			MAX-ACCESS	read-only
			STATUS	current
			::= { hmWanMbus83 16 }

hmWanMbus83Value05		OBJECT-TYPE
			SYNTAX	INTEGER
			MAX-ACCESS	read-only
			STATUS	current
			::= { hmWanMbus83 17 }

hmWanMbus83VIF06		OBJECT-TYPE
			SYNTAX	INTEGER
			MAX-ACCESS	read-only
			STATUS	current
			::= { hmWanMbus83 18 }

hmWanMbus83Value06		OBJECT-TYPE
			SYNTAX	INTEGER
			MAX-ACCESS	read-only
			STATUS	current
			::= { hmWanMbus83 19 }

hmWanMbus83VIF07		OBJECT-TYPE
			SYNTAX	INTEGER
			MAX-ACCESS	read-only
			STATUS	current
			::= { hmWanMbus83 20 }

hmWanMbus83Value07		OBJECT-TYPE
			SYNTAX	INTEGER
			MAX-ACCESS	read-only
			STATUS	current
			::= { hmWanMbus83 21 }

hmWanMbus83VIF08		OBJECT-TYPE
			SYNTAX	INTEGER
			MAX-ACCESS	read-only
			STATUS	current
			::= { hmWanMbus83 22 }

hmWanMbus83Value08		OBJECT-TYPE
			SYNTAX	INTEGER
			MAX-ACCESS	read-only
			STATUS	current
			::= { hmWanMbus83 23 }

hmWanMbus83VIF09		OBJECT-TYPE
			SYNTAX	INTEGER
			MAX-ACCESS	read-only
			STATUS	current
			::= { hmWanMbus83 24 }

hmWanMbus83Value09		OBJECT-TYPE
			SYNTAX	INTEGER
			MAX-ACCESS	read-only
			STATUS	current
			::= { hmWanMbus83 25 }

hmWanMbus83VIF0A		OBJECT-TYPE
			SYNTAX	INTEGER
			MAX-ACCESS	read-only
			STATUS	current
			::= { hmWanMbus83 26 }

hmWanMbus83Value0A		OBJECT-TYPE
			SYNTAX	INTEGER
			MAX-ACCESS	read-only
			STATUS	current
			::= { hmWanMbus83 27 }

hmWanMbus83VIF0B		OBJECT-TYPE
			SYNTAX	INTEGER
			MAX-ACCESS	read-only
			STATUS	current
			::= { hmWanMbus83 28 }

hmWanMbus83Value0B		OBJECT-TYPE
			SYNTAX	INTEGER
			MAX-ACCESS	read-only
			STATUS	current
			::= { hmWanMbus83 29 }

hmWanMbus83VIF0C		OBJECT-TYPE
			SYNTAX	INTEGER
			MAX-ACCESS	read-only
			STATUS	current
			::= { hmWanMbus83 30 }

hmWanMbus83Value0C		OBJECT-TYPE
			SYNTAX	INTEGER
			MAX-ACCESS	read-only
			STATUS	current
			::= { hmWanMbus83 31 }

hmWanMbus83VIF0D		OBJECT-TYPE
			SYNTAX	INTEGER
			MAX-ACCESS	read-only
			STATUS	current
			::= { hmWanMbus83 32 }

hmWanMbus83Value0D		OBJECT-TYPE
			SYNTAX	INTEGER
			MAX-ACCESS	read-only
			STATUS	current
			::= { hmWanMbus83 33 }

hmWanMbus83VIF0E		OBJECT-TYPE
			SYNTAX	INTEGER
			MAX-ACCESS	read-only
			STATUS	current
			::= { hmWanMbus83 34 }

hmWanMbus83Value0E		OBJECT-TYPE
			SYNTAX	INTEGER
			MAX-ACCESS	read-only
			STATUS	current
			::= { hmWanMbus83 35 }

hmWanMbus83VIF0F		OBJECT-TYPE
			SYNTAX	INTEGER
			MAX-ACCESS	read-only
			STATUS	current
			::= { hmWanMbus83 36 }

hmWanMbus83Value0F		OBJECT-TYPE
			SYNTAX	INTEGER
			MAX-ACCESS	read-only
			STATUS	current
			::= { hmWanMbus83 37 }

hmWanMbus83VIF10		OBJECT-TYPE
			SYNTAX	INTEGER
			MAX-ACCESS	read-only
			STATUS	current
			::= { hmWanMbus83 38 }

hmWanMbus83Value10		OBJECT-TYPE
			SYNTAX	INTEGER
			MAX-ACCESS	read-only
			STATUS	current
			::= { hmWanMbus83 39 }

hmWanMbus83VIF11		OBJECT-TYPE
			SYNTAX	INTEGER
			MAX-ACCESS	read-only
			STATUS	current
			::= { hmWanMbus83 40 }

hmWanMbus83Value11		OBJECT-TYPE
			SYNTAX	INTEGER
			MAX-ACCESS	read-only
			STATUS	current
			::= { hmWanMbus83 41 }

hmWanMbus83VIF12		OBJECT-TYPE
			SYNTAX	INTEGER
			MAX-ACCESS	read-only
			STATUS	current
			::= { hmWanMbus83 42 }

hmWanMbus83Value12		OBJECT-TYPE
			SYNTAX	INTEGER
			MAX-ACCESS	read-only
			STATUS	current
			::= { hmWanMbus83 43 }

hmWanMbus83VIF13		OBJECT-TYPE
			SYNTAX	INTEGER
			MAX-ACCESS	read-only
			STATUS	current
			::= { hmWanMbus83 44 }

hmWanMbus83Value13		OBJECT-TYPE
			SYNTAX	INTEGER
			MAX-ACCESS	read-only
			STATUS	current
			::= { hmWanMbus83 45 }

hmWanMbus83VIF14		OBJECT-TYPE
			SYNTAX	INTEGER
			MAX-ACCESS	read-only
			STATUS	current
			::= { hmWanMbus83 46 }

hmWanMbus83Value14		OBJECT-TYPE
			SYNTAX	INTEGER
			MAX-ACCESS	read-only
			STATUS	current
			::= { hmWanMbus83 47 }

hmWanMbus83VIF15		OBJECT-TYPE
			SYNTAX	INTEGER
			MAX-ACCESS	read-only
			STATUS	current
			::= { hmWanMbus83 48 }

hmWanMbus83Value15		OBJECT-TYPE
			SYNTAX	INTEGER
			MAX-ACCESS	read-only
			STATUS	current
			::= { hmWanMbus83 49 }

hmWanMbus83VIF16		OBJECT-TYPE
			SYNTAX	INTEGER
			MAX-ACCESS	read-only
			STATUS	current
			::= { hmWanMbus83 50 }

hmWanMbus83Value16		OBJECT-TYPE
			SYNTAX	INTEGER
			MAX-ACCESS	read-only
			STATUS	current
			::= { hmWanMbus83 51 }

hmWanMbus83VIF17		OBJECT-TYPE
			SYNTAX	INTEGER
			MAX-ACCESS	read-only
			STATUS	current
			::= { hmWanMbus83 52 }

hmWanMbus83Value17		OBJECT-TYPE
			SYNTAX	INTEGER
			MAX-ACCESS	read-only
			STATUS	current
			::= { hmWanMbus83 53 }

hmWanMbus83VIF18		OBJECT-TYPE
			SYNTAX	INTEGER
			MAX-ACCESS	read-only
			STATUS	current
			::= { hmWanMbus83 54 }

hmWanMbus83Value18		OBJECT-TYPE
			SYNTAX	INTEGER
			MAX-ACCESS	read-only
			STATUS	current
			::= { hmWanMbus83 55 }

hmWanMbus83VIF19		OBJECT-TYPE
			SYNTAX	INTEGER
			MAX-ACCESS	read-only
			STATUS	current
			::= { hmWanMbus83 56 }

hmWanMbus83Value19		OBJECT-TYPE
			SYNTAX	INTEGER
			MAX-ACCESS	read-only
			STATUS	current
			::= { hmWanMbus83 57 }

hmWanMbus83VIF1A		OBJECT-TYPE
			SYNTAX	INTEGER
			MAX-ACCESS	read-only
			STATUS	current
			::= { hmWanMbus83 58 }

hmWanMbus83Value1A		OBJECT-TYPE
			SYNTAX	INTEGER
			MAX-ACCESS	read-only
			STATUS	current
			::= { hmWanMbus83 59 }

hmWanMbus83VIF1B		OBJECT-TYPE
			SYNTAX	INTEGER
			MAX-ACCESS	read-only
			STATUS	current
			::= { hmWanMbus83 60 }

hmWanMbus83Value1B		OBJECT-TYPE
			SYNTAX	INTEGER
			MAX-ACCESS	read-only
			STATUS	current
			::= { hmWanMbus83 61 }

hmWanMbus83VIF1C		OBJECT-TYPE
			SYNTAX	INTEGER
			MAX-ACCESS	read-only
			STATUS	current
			::= { hmWanMbus83 62 }

hmWanMbus83Value1C		OBJECT-TYPE
			SYNTAX	INTEGER
			MAX-ACCESS	read-only
			STATUS	current
			::= { hmWanMbus83 63 }

hmWanMbus83VIF1D		OBJECT-TYPE
			SYNTAX	INTEGER
			MAX-ACCESS	read-only
			STATUS	current
			::= { hmWanMbus83 64 }

hmWanMbus83Value1D		OBJECT-TYPE
			SYNTAX	INTEGER
			MAX-ACCESS	read-only
			STATUS	current
			::= { hmWanMbus83 65 }

hmWanMbus83VIF1E		OBJECT-TYPE
			SYNTAX	INTEGER
			MAX-ACCESS	read-only
			STATUS	current
			::= { hmWanMbus83 66 }

hmWanMbus83Value1E		OBJECT-TYPE
			SYNTAX	INTEGER
			MAX-ACCESS	read-only
			STATUS	current
			::= { hmWanMbus83 67 }

hmWanMbus83VIF1F		OBJECT-TYPE
			SYNTAX	INTEGER
			MAX-ACCESS	read-only
			STATUS	current
			::= { hmWanMbus83 68 }

hmWanMbus83Value1F		OBJECT-TYPE
			SYNTAX	INTEGER
			MAX-ACCESS	read-only
			STATUS	current
			::= { hmWanMbus83 69 }

hmWanMbus83VIF20		OBJECT-TYPE
			SYNTAX	INTEGER
			MAX-ACCESS	read-only
			STATUS	current
			::= { hmWanMbus83 70 }

hmWanMbus83Value20		OBJECT-TYPE
			SYNTAX	INTEGER
			MAX-ACCESS	read-only
			STATUS	current
			::= { hmWanMbus83 71 }

hmWanMbus83VIF21		OBJECT-TYPE
			SYNTAX	INTEGER
			MAX-ACCESS	read-only
			STATUS	current
			::= { hmWanMbus83 72 }

hmWanMbus83Value21		OBJECT-TYPE
			SYNTAX	INTEGER
			MAX-ACCESS	read-only
			STATUS	current
			::= { hmWanMbus83 73 }

hmWanMbus83VIF22		OBJECT-TYPE
			SYNTAX	INTEGER
			MAX-ACCESS	read-only
			STATUS	current
			::= { hmWanMbus83 74 }

hmWanMbus83Value22		OBJECT-TYPE
			SYNTAX	INTEGER
			MAX-ACCESS	read-only
			STATUS	current
			::= { hmWanMbus83 75 }

hmWanMbus83VIF23		OBJECT-TYPE
			SYNTAX	INTEGER
			MAX-ACCESS	read-only
			STATUS	current
			::= { hmWanMbus83 76 }

hmWanMbus83Value23		OBJECT-TYPE
			SYNTAX	INTEGER
			MAX-ACCESS	read-only
			STATUS	current
			::= { hmWanMbus83 77 }

hmWanMbus83VIF24		OBJECT-TYPE
			SYNTAX	INTEGER
			MAX-ACCESS	read-only
			STATUS	current
			::= { hmWanMbus83 78 }

hmWanMbus83Value24		OBJECT-TYPE
			SYNTAX	INTEGER
			MAX-ACCESS	read-only
			STATUS	current
			::= { hmWanMbus83 79 }

hmWanMbus83VIF25		OBJECT-TYPE
			SYNTAX	INTEGER
			MAX-ACCESS	read-only
			STATUS	current
			::= { hmWanMbus83 80 }

hmWanMbus83Value25		OBJECT-TYPE
			SYNTAX	INTEGER
			MAX-ACCESS	read-only
			STATUS	current
			::= { hmWanMbus83 81 }

hmWanMbus83VIF26		OBJECT-TYPE
			SYNTAX	INTEGER
			MAX-ACCESS	read-only
			STATUS	current
			::= { hmWanMbus83 82 }

hmWanMbus83Value26		OBJECT-TYPE
			SYNTAX	INTEGER
			MAX-ACCESS	read-only
			STATUS	current
			::= { hmWanMbus83 83 }

hmWanMbus83VIF27		OBJECT-TYPE
			SYNTAX	INTEGER
			MAX-ACCESS	read-only
			STATUS	current
			::= { hmWanMbus83 84 }

hmWanMbus83Value27		OBJECT-TYPE
			SYNTAX	INTEGER
			MAX-ACCESS	read-only
			STATUS	current
			::= { hmWanMbus83 85 }

hmWanMbus83VIF28		OBJECT-TYPE
			SYNTAX	INTEGER
			MAX-ACCESS	read-only
			STATUS	current
			::= { hmWanMbus83 86 }

hmWanMbus83Value28		OBJECT-TYPE
			SYNTAX	INTEGER
			MAX-ACCESS	read-only
			STATUS	current
			::= { hmWanMbus83 87 }

hmWanMbus83VIF29		OBJECT-TYPE
			SYNTAX	INTEGER
			MAX-ACCESS	read-only
			STATUS	current
			::= { hmWanMbus83 88 }

hmWanMbus83Value29		OBJECT-TYPE
			SYNTAX	INTEGER
			MAX-ACCESS	read-only
			STATUS	current
			::= { hmWanMbus83 89 }

hmWanMbus83VIF2A		OBJECT-TYPE
			SYNTAX	INTEGER
			MAX-ACCESS	read-only
			STATUS	current
			::= { hmWanMbus83 90 }

hmWanMbus83Value2A		OBJECT-TYPE
			SYNTAX	INTEGER
			MAX-ACCESS	read-only
			STATUS	current
			::= { hmWanMbus83 91 }

hmWanMbus83VIF2B		OBJECT-TYPE
			SYNTAX	INTEGER
			MAX-ACCESS	read-only
			STATUS	current
			::= { hmWanMbus83 92 }

hmWanMbus83Value2B		OBJECT-TYPE
			SYNTAX	INTEGER
			MAX-ACCESS	read-only
			STATUS	current
			::= { hmWanMbus83 93 }

hmWanMbus83VIF2C		OBJECT-TYPE
			SYNTAX	INTEGER
			MAX-ACCESS	read-only
			STATUS	current
			::= { hmWanMbus83 94 }

hmWanMbus83Value2C		OBJECT-TYPE
			SYNTAX	INTEGER
			MAX-ACCESS	read-only
			STATUS	current
			::= { hmWanMbus83 95 }

hmWanMbus83VIF2D		OBJECT-TYPE
			SYNTAX	INTEGER
			MAX-ACCESS	read-only
			STATUS	current
			::= { hmWanMbus83 96 }

hmWanMbus83Value2D		OBJECT-TYPE
			SYNTAX	INTEGER
			MAX-ACCESS	read-only
			STATUS	current
			::= { hmWanMbus83 97 }

hmWanMbus83VIF2E		OBJECT-TYPE
			SYNTAX	INTEGER
			MAX-ACCESS	read-only
			STATUS	current
			::= { hmWanMbus83 98 }

hmWanMbus83Value2E		OBJECT-TYPE
			SYNTAX	INTEGER
			MAX-ACCESS	read-only
			STATUS	current
			::= { hmWanMbus83 99 }

hmWanMbus83VIF2F		OBJECT-TYPE
			SYNTAX	INTEGER
			MAX-ACCESS	read-only
			STATUS	current
			::= { hmWanMbus83 100 }

hmWanMbus83Value2F		OBJECT-TYPE
			SYNTAX	INTEGER
			MAX-ACCESS	read-only
			STATUS	current
			::= { hmWanMbus83 101 }

hmWanMbus84			OBJECT IDENTIFIER ::= { hmWanMbus 132 }

hmWanMbus84IdNumber		OBJECT-TYPE
			SYNTAX	Gauge32
			MAX-ACCESS	read-only
			STATUS	current
			::= { hmWanMbus84 1 }

hmWanMbus84Manufacturer	OBJECT-TYPE
			SYNTAX	Gauge32
			MAX-ACCESS	read-only
			STATUS	current
			::= { hmWanMbus84 2 }

hmWanMbus84Version		OBJECT-TYPE
			SYNTAX	Gauge32
			MAX-ACCESS	read-only
			STATUS	current
			::= { hmWanMbus84 3 }

hmWanMbus84Medium		OBJECT-TYPE
			SYNTAX	Gauge32
			MAX-ACCESS	read-only
			STATUS	current
			::= { hmWanMbus84 4 }

hmWanMbus84Status		OBJECT-TYPE
			SYNTAX	Gauge32
			MAX-ACCESS	read-only
			STATUS	current
			::= { hmWanMbus84 5 }

hmWanMbus84VIF00		OBJECT-TYPE
			SYNTAX	INTEGER
			MAX-ACCESS	read-only
			STATUS	current
			::= { hmWanMbus84 6 }

hmWanMbus84Value00		OBJECT-TYPE
			SYNTAX	INTEGER
			MAX-ACCESS	read-only
			STATUS	current
			::= { hmWanMbus84 7 }

hmWanMbus84VIF01		OBJECT-TYPE
			SYNTAX	INTEGER
			MAX-ACCESS	read-only
			STATUS	current
			::= { hmWanMbus84 8 }

hmWanMbus84Value01		OBJECT-TYPE
			SYNTAX	INTEGER
			MAX-ACCESS	read-only
			STATUS	current
			::= { hmWanMbus84 9 }

hmWanMbus84VIF02		OBJECT-TYPE
			SYNTAX	INTEGER
			MAX-ACCESS	read-only
			STATUS	current
			::= { hmWanMbus84 10 }

hmWanMbus84Value02		OBJECT-TYPE
			SYNTAX	INTEGER
			MAX-ACCESS	read-only
			STATUS	current
			::= { hmWanMbus84 11 }

hmWanMbus84VIF03		OBJECT-TYPE
			SYNTAX	INTEGER
			MAX-ACCESS	read-only
			STATUS	current
			::= { hmWanMbus84 12 }

hmWanMbus84Value03		OBJECT-TYPE
			SYNTAX	INTEGER
			MAX-ACCESS	read-only
			STATUS	current
			::= { hmWanMbus84 13 }

hmWanMbus84VIF04		OBJECT-TYPE
			SYNTAX	INTEGER
			MAX-ACCESS	read-only
			STATUS	current
			::= { hmWanMbus84 14 }

hmWanMbus84Value04		OBJECT-TYPE
			SYNTAX	INTEGER
			MAX-ACCESS	read-only
			STATUS	current
			::= { hmWanMbus84 15 }

hmWanMbus84VIF05		OBJECT-TYPE
			SYNTAX	INTEGER
			MAX-ACCESS	read-only
			STATUS	current
			::= { hmWanMbus84 16 }

hmWanMbus84Value05		OBJECT-TYPE
			SYNTAX	INTEGER
			MAX-ACCESS	read-only
			STATUS	current
			::= { hmWanMbus84 17 }

hmWanMbus84VIF06		OBJECT-TYPE
			SYNTAX	INTEGER
			MAX-ACCESS	read-only
			STATUS	current
			::= { hmWanMbus84 18 }

hmWanMbus84Value06		OBJECT-TYPE
			SYNTAX	INTEGER
			MAX-ACCESS	read-only
			STATUS	current
			::= { hmWanMbus84 19 }

hmWanMbus84VIF07		OBJECT-TYPE
			SYNTAX	INTEGER
			MAX-ACCESS	read-only
			STATUS	current
			::= { hmWanMbus84 20 }

hmWanMbus84Value07		OBJECT-TYPE
			SYNTAX	INTEGER
			MAX-ACCESS	read-only
			STATUS	current
			::= { hmWanMbus84 21 }

hmWanMbus84VIF08		OBJECT-TYPE
			SYNTAX	INTEGER
			MAX-ACCESS	read-only
			STATUS	current
			::= { hmWanMbus84 22 }

hmWanMbus84Value08		OBJECT-TYPE
			SYNTAX	INTEGER
			MAX-ACCESS	read-only
			STATUS	current
			::= { hmWanMbus84 23 }

hmWanMbus84VIF09		OBJECT-TYPE
			SYNTAX	INTEGER
			MAX-ACCESS	read-only
			STATUS	current
			::= { hmWanMbus84 24 }

hmWanMbus84Value09		OBJECT-TYPE
			SYNTAX	INTEGER
			MAX-ACCESS	read-only
			STATUS	current
			::= { hmWanMbus84 25 }

hmWanMbus84VIF0A		OBJECT-TYPE
			SYNTAX	INTEGER
			MAX-ACCESS	read-only
			STATUS	current
			::= { hmWanMbus84 26 }

hmWanMbus84Value0A		OBJECT-TYPE
			SYNTAX	INTEGER
			MAX-ACCESS	read-only
			STATUS	current
			::= { hmWanMbus84 27 }

hmWanMbus84VIF0B		OBJECT-TYPE
			SYNTAX	INTEGER
			MAX-ACCESS	read-only
			STATUS	current
			::= { hmWanMbus84 28 }

hmWanMbus84Value0B		OBJECT-TYPE
			SYNTAX	INTEGER
			MAX-ACCESS	read-only
			STATUS	current
			::= { hmWanMbus84 29 }

hmWanMbus84VIF0C		OBJECT-TYPE
			SYNTAX	INTEGER
			MAX-ACCESS	read-only
			STATUS	current
			::= { hmWanMbus84 30 }

hmWanMbus84Value0C		OBJECT-TYPE
			SYNTAX	INTEGER
			MAX-ACCESS	read-only
			STATUS	current
			::= { hmWanMbus84 31 }

hmWanMbus84VIF0D		OBJECT-TYPE
			SYNTAX	INTEGER
			MAX-ACCESS	read-only
			STATUS	current
			::= { hmWanMbus84 32 }

hmWanMbus84Value0D		OBJECT-TYPE
			SYNTAX	INTEGER
			MAX-ACCESS	read-only
			STATUS	current
			::= { hmWanMbus84 33 }

hmWanMbus84VIF0E		OBJECT-TYPE
			SYNTAX	INTEGER
			MAX-ACCESS	read-only
			STATUS	current
			::= { hmWanMbus84 34 }

hmWanMbus84Value0E		OBJECT-TYPE
			SYNTAX	INTEGER
			MAX-ACCESS	read-only
			STATUS	current
			::= { hmWanMbus84 35 }

hmWanMbus84VIF0F		OBJECT-TYPE
			SYNTAX	INTEGER
			MAX-ACCESS	read-only
			STATUS	current
			::= { hmWanMbus84 36 }

hmWanMbus84Value0F		OBJECT-TYPE
			SYNTAX	INTEGER
			MAX-ACCESS	read-only
			STATUS	current
			::= { hmWanMbus84 37 }

hmWanMbus84VIF10		OBJECT-TYPE
			SYNTAX	INTEGER
			MAX-ACCESS	read-only
			STATUS	current
			::= { hmWanMbus84 38 }

hmWanMbus84Value10		OBJECT-TYPE
			SYNTAX	INTEGER
			MAX-ACCESS	read-only
			STATUS	current
			::= { hmWanMbus84 39 }

hmWanMbus84VIF11		OBJECT-TYPE
			SYNTAX	INTEGER
			MAX-ACCESS	read-only
			STATUS	current
			::= { hmWanMbus84 40 }

hmWanMbus84Value11		OBJECT-TYPE
			SYNTAX	INTEGER
			MAX-ACCESS	read-only
			STATUS	current
			::= { hmWanMbus84 41 }

hmWanMbus84VIF12		OBJECT-TYPE
			SYNTAX	INTEGER
			MAX-ACCESS	read-only
			STATUS	current
			::= { hmWanMbus84 42 }

hmWanMbus84Value12		OBJECT-TYPE
			SYNTAX	INTEGER
			MAX-ACCESS	read-only
			STATUS	current
			::= { hmWanMbus84 43 }

hmWanMbus84VIF13		OBJECT-TYPE
			SYNTAX	INTEGER
			MAX-ACCESS	read-only
			STATUS	current
			::= { hmWanMbus84 44 }

hmWanMbus84Value13		OBJECT-TYPE
			SYNTAX	INTEGER
			MAX-ACCESS	read-only
			STATUS	current
			::= { hmWanMbus84 45 }

hmWanMbus84VIF14		OBJECT-TYPE
			SYNTAX	INTEGER
			MAX-ACCESS	read-only
			STATUS	current
			::= { hmWanMbus84 46 }

hmWanMbus84Value14		OBJECT-TYPE
			SYNTAX	INTEGER
			MAX-ACCESS	read-only
			STATUS	current
			::= { hmWanMbus84 47 }

hmWanMbus84VIF15		OBJECT-TYPE
			SYNTAX	INTEGER
			MAX-ACCESS	read-only
			STATUS	current
			::= { hmWanMbus84 48 }

hmWanMbus84Value15		OBJECT-TYPE
			SYNTAX	INTEGER
			MAX-ACCESS	read-only
			STATUS	current
			::= { hmWanMbus84 49 }

hmWanMbus84VIF16		OBJECT-TYPE
			SYNTAX	INTEGER
			MAX-ACCESS	read-only
			STATUS	current
			::= { hmWanMbus84 50 }

hmWanMbus84Value16		OBJECT-TYPE
			SYNTAX	INTEGER
			MAX-ACCESS	read-only
			STATUS	current
			::= { hmWanMbus84 51 }

hmWanMbus84VIF17		OBJECT-TYPE
			SYNTAX	INTEGER
			MAX-ACCESS	read-only
			STATUS	current
			::= { hmWanMbus84 52 }

hmWanMbus84Value17		OBJECT-TYPE
			SYNTAX	INTEGER
			MAX-ACCESS	read-only
			STATUS	current
			::= { hmWanMbus84 53 }

hmWanMbus84VIF18		OBJECT-TYPE
			SYNTAX	INTEGER
			MAX-ACCESS	read-only
			STATUS	current
			::= { hmWanMbus84 54 }

hmWanMbus84Value18		OBJECT-TYPE
			SYNTAX	INTEGER
			MAX-ACCESS	read-only
			STATUS	current
			::= { hmWanMbus84 55 }

hmWanMbus84VIF19		OBJECT-TYPE
			SYNTAX	INTEGER
			MAX-ACCESS	read-only
			STATUS	current
			::= { hmWanMbus84 56 }

hmWanMbus84Value19		OBJECT-TYPE
			SYNTAX	INTEGER
			MAX-ACCESS	read-only
			STATUS	current
			::= { hmWanMbus84 57 }

hmWanMbus84VIF1A		OBJECT-TYPE
			SYNTAX	INTEGER
			MAX-ACCESS	read-only
			STATUS	current
			::= { hmWanMbus84 58 }

hmWanMbus84Value1A		OBJECT-TYPE
			SYNTAX	INTEGER
			MAX-ACCESS	read-only
			STATUS	current
			::= { hmWanMbus84 59 }

hmWanMbus84VIF1B		OBJECT-TYPE
			SYNTAX	INTEGER
			MAX-ACCESS	read-only
			STATUS	current
			::= { hmWanMbus84 60 }

hmWanMbus84Value1B		OBJECT-TYPE
			SYNTAX	INTEGER
			MAX-ACCESS	read-only
			STATUS	current
			::= { hmWanMbus84 61 }

hmWanMbus84VIF1C		OBJECT-TYPE
			SYNTAX	INTEGER
			MAX-ACCESS	read-only
			STATUS	current
			::= { hmWanMbus84 62 }

hmWanMbus84Value1C		OBJECT-TYPE
			SYNTAX	INTEGER
			MAX-ACCESS	read-only
			STATUS	current
			::= { hmWanMbus84 63 }

hmWanMbus84VIF1D		OBJECT-TYPE
			SYNTAX	INTEGER
			MAX-ACCESS	read-only
			STATUS	current
			::= { hmWanMbus84 64 }

hmWanMbus84Value1D		OBJECT-TYPE
			SYNTAX	INTEGER
			MAX-ACCESS	read-only
			STATUS	current
			::= { hmWanMbus84 65 }

hmWanMbus84VIF1E		OBJECT-TYPE
			SYNTAX	INTEGER
			MAX-ACCESS	read-only
			STATUS	current
			::= { hmWanMbus84 66 }

hmWanMbus84Value1E		OBJECT-TYPE
			SYNTAX	INTEGER
			MAX-ACCESS	read-only
			STATUS	current
			::= { hmWanMbus84 67 }

hmWanMbus84VIF1F		OBJECT-TYPE
			SYNTAX	INTEGER
			MAX-ACCESS	read-only
			STATUS	current
			::= { hmWanMbus84 68 }

hmWanMbus84Value1F		OBJECT-TYPE
			SYNTAX	INTEGER
			MAX-ACCESS	read-only
			STATUS	current
			::= { hmWanMbus84 69 }

hmWanMbus84VIF20		OBJECT-TYPE
			SYNTAX	INTEGER
			MAX-ACCESS	read-only
			STATUS	current
			::= { hmWanMbus84 70 }

hmWanMbus84Value20		OBJECT-TYPE
			SYNTAX	INTEGER
			MAX-ACCESS	read-only
			STATUS	current
			::= { hmWanMbus84 71 }

hmWanMbus84VIF21		OBJECT-TYPE
			SYNTAX	INTEGER
			MAX-ACCESS	read-only
			STATUS	current
			::= { hmWanMbus84 72 }

hmWanMbus84Value21		OBJECT-TYPE
			SYNTAX	INTEGER
			MAX-ACCESS	read-only
			STATUS	current
			::= { hmWanMbus84 73 }

hmWanMbus84VIF22		OBJECT-TYPE
			SYNTAX	INTEGER
			MAX-ACCESS	read-only
			STATUS	current
			::= { hmWanMbus84 74 }

hmWanMbus84Value22		OBJECT-TYPE
			SYNTAX	INTEGER
			MAX-ACCESS	read-only
			STATUS	current
			::= { hmWanMbus84 75 }

hmWanMbus84VIF23		OBJECT-TYPE
			SYNTAX	INTEGER
			MAX-ACCESS	read-only
			STATUS	current
			::= { hmWanMbus84 76 }

hmWanMbus84Value23		OBJECT-TYPE
			SYNTAX	INTEGER
			MAX-ACCESS	read-only
			STATUS	current
			::= { hmWanMbus84 77 }

hmWanMbus84VIF24		OBJECT-TYPE
			SYNTAX	INTEGER
			MAX-ACCESS	read-only
			STATUS	current
			::= { hmWanMbus84 78 }

hmWanMbus84Value24		OBJECT-TYPE
			SYNTAX	INTEGER
			MAX-ACCESS	read-only
			STATUS	current
			::= { hmWanMbus84 79 }

hmWanMbus84VIF25		OBJECT-TYPE
			SYNTAX	INTEGER
			MAX-ACCESS	read-only
			STATUS	current
			::= { hmWanMbus84 80 }

hmWanMbus84Value25		OBJECT-TYPE
			SYNTAX	INTEGER
			MAX-ACCESS	read-only
			STATUS	current
			::= { hmWanMbus84 81 }

hmWanMbus84VIF26		OBJECT-TYPE
			SYNTAX	INTEGER
			MAX-ACCESS	read-only
			STATUS	current
			::= { hmWanMbus84 82 }

hmWanMbus84Value26		OBJECT-TYPE
			SYNTAX	INTEGER
			MAX-ACCESS	read-only
			STATUS	current
			::= { hmWanMbus84 83 }

hmWanMbus84VIF27		OBJECT-TYPE
			SYNTAX	INTEGER
			MAX-ACCESS	read-only
			STATUS	current
			::= { hmWanMbus84 84 }

hmWanMbus84Value27		OBJECT-TYPE
			SYNTAX	INTEGER
			MAX-ACCESS	read-only
			STATUS	current
			::= { hmWanMbus84 85 }

hmWanMbus84VIF28		OBJECT-TYPE
			SYNTAX	INTEGER
			MAX-ACCESS	read-only
			STATUS	current
			::= { hmWanMbus84 86 }

hmWanMbus84Value28		OBJECT-TYPE
			SYNTAX	INTEGER
			MAX-ACCESS	read-only
			STATUS	current
			::= { hmWanMbus84 87 }

hmWanMbus84VIF29		OBJECT-TYPE
			SYNTAX	INTEGER
			MAX-ACCESS	read-only
			STATUS	current
			::= { hmWanMbus84 88 }

hmWanMbus84Value29		OBJECT-TYPE
			SYNTAX	INTEGER
			MAX-ACCESS	read-only
			STATUS	current
			::= { hmWanMbus84 89 }

hmWanMbus84VIF2A		OBJECT-TYPE
			SYNTAX	INTEGER
			MAX-ACCESS	read-only
			STATUS	current
			::= { hmWanMbus84 90 }

hmWanMbus84Value2A		OBJECT-TYPE
			SYNTAX	INTEGER
			MAX-ACCESS	read-only
			STATUS	current
			::= { hmWanMbus84 91 }

hmWanMbus84VIF2B		OBJECT-TYPE
			SYNTAX	INTEGER
			MAX-ACCESS	read-only
			STATUS	current
			::= { hmWanMbus84 92 }

hmWanMbus84Value2B		OBJECT-TYPE
			SYNTAX	INTEGER
			MAX-ACCESS	read-only
			STATUS	current
			::= { hmWanMbus84 93 }

hmWanMbus84VIF2C		OBJECT-TYPE
			SYNTAX	INTEGER
			MAX-ACCESS	read-only
			STATUS	current
			::= { hmWanMbus84 94 }

hmWanMbus84Value2C		OBJECT-TYPE
			SYNTAX	INTEGER
			MAX-ACCESS	read-only
			STATUS	current
			::= { hmWanMbus84 95 }

hmWanMbus84VIF2D		OBJECT-TYPE
			SYNTAX	INTEGER
			MAX-ACCESS	read-only
			STATUS	current
			::= { hmWanMbus84 96 }

hmWanMbus84Value2D		OBJECT-TYPE
			SYNTAX	INTEGER
			MAX-ACCESS	read-only
			STATUS	current
			::= { hmWanMbus84 97 }

hmWanMbus84VIF2E		OBJECT-TYPE
			SYNTAX	INTEGER
			MAX-ACCESS	read-only
			STATUS	current
			::= { hmWanMbus84 98 }

hmWanMbus84Value2E		OBJECT-TYPE
			SYNTAX	INTEGER
			MAX-ACCESS	read-only
			STATUS	current
			::= { hmWanMbus84 99 }

hmWanMbus84VIF2F		OBJECT-TYPE
			SYNTAX	INTEGER
			MAX-ACCESS	read-only
			STATUS	current
			::= { hmWanMbus84 100 }

hmWanMbus84Value2F		OBJECT-TYPE
			SYNTAX	INTEGER
			MAX-ACCESS	read-only
			STATUS	current
			::= { hmWanMbus84 101 }

hmWanMbus85			OBJECT IDENTIFIER ::= { hmWanMbus 133 }

hmWanMbus85IdNumber		OBJECT-TYPE
			SYNTAX	Gauge32
			MAX-ACCESS	read-only
			STATUS	current
			::= { hmWanMbus85 1 }

hmWanMbus85Manufacturer	OBJECT-TYPE
			SYNTAX	Gauge32
			MAX-ACCESS	read-only
			STATUS	current
			::= { hmWanMbus85 2 }

hmWanMbus85Version		OBJECT-TYPE
			SYNTAX	Gauge32
			MAX-ACCESS	read-only
			STATUS	current
			::= { hmWanMbus85 3 }

hmWanMbus85Medium		OBJECT-TYPE
			SYNTAX	Gauge32
			MAX-ACCESS	read-only
			STATUS	current
			::= { hmWanMbus85 4 }

hmWanMbus85Status		OBJECT-TYPE
			SYNTAX	Gauge32
			MAX-ACCESS	read-only
			STATUS	current
			::= { hmWanMbus85 5 }

hmWanMbus85VIF00		OBJECT-TYPE
			SYNTAX	INTEGER
			MAX-ACCESS	read-only
			STATUS	current
			::= { hmWanMbus85 6 }

hmWanMbus85Value00		OBJECT-TYPE
			SYNTAX	INTEGER
			MAX-ACCESS	read-only
			STATUS	current
			::= { hmWanMbus85 7 }

hmWanMbus85VIF01		OBJECT-TYPE
			SYNTAX	INTEGER
			MAX-ACCESS	read-only
			STATUS	current
			::= { hmWanMbus85 8 }

hmWanMbus85Value01		OBJECT-TYPE
			SYNTAX	INTEGER
			MAX-ACCESS	read-only
			STATUS	current
			::= { hmWanMbus85 9 }

hmWanMbus85VIF02		OBJECT-TYPE
			SYNTAX	INTEGER
			MAX-ACCESS	read-only
			STATUS	current
			::= { hmWanMbus85 10 }

hmWanMbus85Value02		OBJECT-TYPE
			SYNTAX	INTEGER
			MAX-ACCESS	read-only
			STATUS	current
			::= { hmWanMbus85 11 }

hmWanMbus85VIF03		OBJECT-TYPE
			SYNTAX	INTEGER
			MAX-ACCESS	read-only
			STATUS	current
			::= { hmWanMbus85 12 }

hmWanMbus85Value03		OBJECT-TYPE
			SYNTAX	INTEGER
			MAX-ACCESS	read-only
			STATUS	current
			::= { hmWanMbus85 13 }

hmWanMbus85VIF04		OBJECT-TYPE
			SYNTAX	INTEGER
			MAX-ACCESS	read-only
			STATUS	current
			::= { hmWanMbus85 14 }

hmWanMbus85Value04		OBJECT-TYPE
			SYNTAX	INTEGER
			MAX-ACCESS	read-only
			STATUS	current
			::= { hmWanMbus85 15 }

hmWanMbus85VIF05		OBJECT-TYPE
			SYNTAX	INTEGER
			MAX-ACCESS	read-only
			STATUS	current
			::= { hmWanMbus85 16 }

hmWanMbus85Value05		OBJECT-TYPE
			SYNTAX	INTEGER
			MAX-ACCESS	read-only
			STATUS	current
			::= { hmWanMbus85 17 }

hmWanMbus85VIF06		OBJECT-TYPE
			SYNTAX	INTEGER
			MAX-ACCESS	read-only
			STATUS	current
			::= { hmWanMbus85 18 }

hmWanMbus85Value06		OBJECT-TYPE
			SYNTAX	INTEGER
			MAX-ACCESS	read-only
			STATUS	current
			::= { hmWanMbus85 19 }

hmWanMbus85VIF07		OBJECT-TYPE
			SYNTAX	INTEGER
			MAX-ACCESS	read-only
			STATUS	current
			::= { hmWanMbus85 20 }

hmWanMbus85Value07		OBJECT-TYPE
			SYNTAX	INTEGER
			MAX-ACCESS	read-only
			STATUS	current
			::= { hmWanMbus85 21 }

hmWanMbus85VIF08		OBJECT-TYPE
			SYNTAX	INTEGER
			MAX-ACCESS	read-only
			STATUS	current
			::= { hmWanMbus85 22 }

hmWanMbus85Value08		OBJECT-TYPE
			SYNTAX	INTEGER
			MAX-ACCESS	read-only
			STATUS	current
			::= { hmWanMbus85 23 }

hmWanMbus85VIF09		OBJECT-TYPE
			SYNTAX	INTEGER
			MAX-ACCESS	read-only
			STATUS	current
			::= { hmWanMbus85 24 }

hmWanMbus85Value09		OBJECT-TYPE
			SYNTAX	INTEGER
			MAX-ACCESS	read-only
			STATUS	current
			::= { hmWanMbus85 25 }

hmWanMbus85VIF0A		OBJECT-TYPE
			SYNTAX	INTEGER
			MAX-ACCESS	read-only
			STATUS	current
			::= { hmWanMbus85 26 }

hmWanMbus85Value0A		OBJECT-TYPE
			SYNTAX	INTEGER
			MAX-ACCESS	read-only
			STATUS	current
			::= { hmWanMbus85 27 }

hmWanMbus85VIF0B		OBJECT-TYPE
			SYNTAX	INTEGER
			MAX-ACCESS	read-only
			STATUS	current
			::= { hmWanMbus85 28 }

hmWanMbus85Value0B		OBJECT-TYPE
			SYNTAX	INTEGER
			MAX-ACCESS	read-only
			STATUS	current
			::= { hmWanMbus85 29 }

hmWanMbus85VIF0C		OBJECT-TYPE
			SYNTAX	INTEGER
			MAX-ACCESS	read-only
			STATUS	current
			::= { hmWanMbus85 30 }

hmWanMbus85Value0C		OBJECT-TYPE
			SYNTAX	INTEGER
			MAX-ACCESS	read-only
			STATUS	current
			::= { hmWanMbus85 31 }

hmWanMbus85VIF0D		OBJECT-TYPE
			SYNTAX	INTEGER
			MAX-ACCESS	read-only
			STATUS	current
			::= { hmWanMbus85 32 }

hmWanMbus85Value0D		OBJECT-TYPE
			SYNTAX	INTEGER
			MAX-ACCESS	read-only
			STATUS	current
			::= { hmWanMbus85 33 }

hmWanMbus85VIF0E		OBJECT-TYPE
			SYNTAX	INTEGER
			MAX-ACCESS	read-only
			STATUS	current
			::= { hmWanMbus85 34 }

hmWanMbus85Value0E		OBJECT-TYPE
			SYNTAX	INTEGER
			MAX-ACCESS	read-only
			STATUS	current
			::= { hmWanMbus85 35 }

hmWanMbus85VIF0F		OBJECT-TYPE
			SYNTAX	INTEGER
			MAX-ACCESS	read-only
			STATUS	current
			::= { hmWanMbus85 36 }

hmWanMbus85Value0F		OBJECT-TYPE
			SYNTAX	INTEGER
			MAX-ACCESS	read-only
			STATUS	current
			::= { hmWanMbus85 37 }

hmWanMbus85VIF10		OBJECT-TYPE
			SYNTAX	INTEGER
			MAX-ACCESS	read-only
			STATUS	current
			::= { hmWanMbus85 38 }

hmWanMbus85Value10		OBJECT-TYPE
			SYNTAX	INTEGER
			MAX-ACCESS	read-only
			STATUS	current
			::= { hmWanMbus85 39 }

hmWanMbus85VIF11		OBJECT-TYPE
			SYNTAX	INTEGER
			MAX-ACCESS	read-only
			STATUS	current
			::= { hmWanMbus85 40 }

hmWanMbus85Value11		OBJECT-TYPE
			SYNTAX	INTEGER
			MAX-ACCESS	read-only
			STATUS	current
			::= { hmWanMbus85 41 }

hmWanMbus85VIF12		OBJECT-TYPE
			SYNTAX	INTEGER
			MAX-ACCESS	read-only
			STATUS	current
			::= { hmWanMbus85 42 }

hmWanMbus85Value12		OBJECT-TYPE
			SYNTAX	INTEGER
			MAX-ACCESS	read-only
			STATUS	current
			::= { hmWanMbus85 43 }

hmWanMbus85VIF13		OBJECT-TYPE
			SYNTAX	INTEGER
			MAX-ACCESS	read-only
			STATUS	current
			::= { hmWanMbus85 44 }

hmWanMbus85Value13		OBJECT-TYPE
			SYNTAX	INTEGER
			MAX-ACCESS	read-only
			STATUS	current
			::= { hmWanMbus85 45 }

hmWanMbus85VIF14		OBJECT-TYPE
			SYNTAX	INTEGER
			MAX-ACCESS	read-only
			STATUS	current
			::= { hmWanMbus85 46 }

hmWanMbus85Value14		OBJECT-TYPE
			SYNTAX	INTEGER
			MAX-ACCESS	read-only
			STATUS	current
			::= { hmWanMbus85 47 }

hmWanMbus85VIF15		OBJECT-TYPE
			SYNTAX	INTEGER
			MAX-ACCESS	read-only
			STATUS	current
			::= { hmWanMbus85 48 }

hmWanMbus85Value15		OBJECT-TYPE
			SYNTAX	INTEGER
			MAX-ACCESS	read-only
			STATUS	current
			::= { hmWanMbus85 49 }

hmWanMbus85VIF16		OBJECT-TYPE
			SYNTAX	INTEGER
			MAX-ACCESS	read-only
			STATUS	current
			::= { hmWanMbus85 50 }

hmWanMbus85Value16		OBJECT-TYPE
			SYNTAX	INTEGER
			MAX-ACCESS	read-only
			STATUS	current
			::= { hmWanMbus85 51 }

hmWanMbus85VIF17		OBJECT-TYPE
			SYNTAX	INTEGER
			MAX-ACCESS	read-only
			STATUS	current
			::= { hmWanMbus85 52 }

hmWanMbus85Value17		OBJECT-TYPE
			SYNTAX	INTEGER
			MAX-ACCESS	read-only
			STATUS	current
			::= { hmWanMbus85 53 }

hmWanMbus85VIF18		OBJECT-TYPE
			SYNTAX	INTEGER
			MAX-ACCESS	read-only
			STATUS	current
			::= { hmWanMbus85 54 }

hmWanMbus85Value18		OBJECT-TYPE
			SYNTAX	INTEGER
			MAX-ACCESS	read-only
			STATUS	current
			::= { hmWanMbus85 55 }

hmWanMbus85VIF19		OBJECT-TYPE
			SYNTAX	INTEGER
			MAX-ACCESS	read-only
			STATUS	current
			::= { hmWanMbus85 56 }

hmWanMbus85Value19		OBJECT-TYPE
			SYNTAX	INTEGER
			MAX-ACCESS	read-only
			STATUS	current
			::= { hmWanMbus85 57 }

hmWanMbus85VIF1A		OBJECT-TYPE
			SYNTAX	INTEGER
			MAX-ACCESS	read-only
			STATUS	current
			::= { hmWanMbus85 58 }

hmWanMbus85Value1A		OBJECT-TYPE
			SYNTAX	INTEGER
			MAX-ACCESS	read-only
			STATUS	current
			::= { hmWanMbus85 59 }

hmWanMbus85VIF1B		OBJECT-TYPE
			SYNTAX	INTEGER
			MAX-ACCESS	read-only
			STATUS	current
			::= { hmWanMbus85 60 }

hmWanMbus85Value1B		OBJECT-TYPE
			SYNTAX	INTEGER
			MAX-ACCESS	read-only
			STATUS	current
			::= { hmWanMbus85 61 }

hmWanMbus85VIF1C		OBJECT-TYPE
			SYNTAX	INTEGER
			MAX-ACCESS	read-only
			STATUS	current
			::= { hmWanMbus85 62 }

hmWanMbus85Value1C		OBJECT-TYPE
			SYNTAX	INTEGER
			MAX-ACCESS	read-only
			STATUS	current
			::= { hmWanMbus85 63 }

hmWanMbus85VIF1D		OBJECT-TYPE
			SYNTAX	INTEGER
			MAX-ACCESS	read-only
			STATUS	current
			::= { hmWanMbus85 64 }

hmWanMbus85Value1D		OBJECT-TYPE
			SYNTAX	INTEGER
			MAX-ACCESS	read-only
			STATUS	current
			::= { hmWanMbus85 65 }

hmWanMbus85VIF1E		OBJECT-TYPE
			SYNTAX	INTEGER
			MAX-ACCESS	read-only
			STATUS	current
			::= { hmWanMbus85 66 }

hmWanMbus85Value1E		OBJECT-TYPE
			SYNTAX	INTEGER
			MAX-ACCESS	read-only
			STATUS	current
			::= { hmWanMbus85 67 }

hmWanMbus85VIF1F		OBJECT-TYPE
			SYNTAX	INTEGER
			MAX-ACCESS	read-only
			STATUS	current
			::= { hmWanMbus85 68 }

hmWanMbus85Value1F		OBJECT-TYPE
			SYNTAX	INTEGER
			MAX-ACCESS	read-only
			STATUS	current
			::= { hmWanMbus85 69 }

hmWanMbus85VIF20		OBJECT-TYPE
			SYNTAX	INTEGER
			MAX-ACCESS	read-only
			STATUS	current
			::= { hmWanMbus85 70 }

hmWanMbus85Value20		OBJECT-TYPE
			SYNTAX	INTEGER
			MAX-ACCESS	read-only
			STATUS	current
			::= { hmWanMbus85 71 }

hmWanMbus85VIF21		OBJECT-TYPE
			SYNTAX	INTEGER
			MAX-ACCESS	read-only
			STATUS	current
			::= { hmWanMbus85 72 }

hmWanMbus85Value21		OBJECT-TYPE
			SYNTAX	INTEGER
			MAX-ACCESS	read-only
			STATUS	current
			::= { hmWanMbus85 73 }

hmWanMbus85VIF22		OBJECT-TYPE
			SYNTAX	INTEGER
			MAX-ACCESS	read-only
			STATUS	current
			::= { hmWanMbus85 74 }

hmWanMbus85Value22		OBJECT-TYPE
			SYNTAX	INTEGER
			MAX-ACCESS	read-only
			STATUS	current
			::= { hmWanMbus85 75 }

hmWanMbus85VIF23		OBJECT-TYPE
			SYNTAX	INTEGER
			MAX-ACCESS	read-only
			STATUS	current
			::= { hmWanMbus85 76 }

hmWanMbus85Value23		OBJECT-TYPE
			SYNTAX	INTEGER
			MAX-ACCESS	read-only
			STATUS	current
			::= { hmWanMbus85 77 }

hmWanMbus85VIF24		OBJECT-TYPE
			SYNTAX	INTEGER
			MAX-ACCESS	read-only
			STATUS	current
			::= { hmWanMbus85 78 }

hmWanMbus85Value24		OBJECT-TYPE
			SYNTAX	INTEGER
			MAX-ACCESS	read-only
			STATUS	current
			::= { hmWanMbus85 79 }

hmWanMbus85VIF25		OBJECT-TYPE
			SYNTAX	INTEGER
			MAX-ACCESS	read-only
			STATUS	current
			::= { hmWanMbus85 80 }

hmWanMbus85Value25		OBJECT-TYPE
			SYNTAX	INTEGER
			MAX-ACCESS	read-only
			STATUS	current
			::= { hmWanMbus85 81 }

hmWanMbus85VIF26		OBJECT-TYPE
			SYNTAX	INTEGER
			MAX-ACCESS	read-only
			STATUS	current
			::= { hmWanMbus85 82 }

hmWanMbus85Value26		OBJECT-TYPE
			SYNTAX	INTEGER
			MAX-ACCESS	read-only
			STATUS	current
			::= { hmWanMbus85 83 }

hmWanMbus85VIF27		OBJECT-TYPE
			SYNTAX	INTEGER
			MAX-ACCESS	read-only
			STATUS	current
			::= { hmWanMbus85 84 }

hmWanMbus85Value27		OBJECT-TYPE
			SYNTAX	INTEGER
			MAX-ACCESS	read-only
			STATUS	current
			::= { hmWanMbus85 85 }

hmWanMbus85VIF28		OBJECT-TYPE
			SYNTAX	INTEGER
			MAX-ACCESS	read-only
			STATUS	current
			::= { hmWanMbus85 86 }

hmWanMbus85Value28		OBJECT-TYPE
			SYNTAX	INTEGER
			MAX-ACCESS	read-only
			STATUS	current
			::= { hmWanMbus85 87 }

hmWanMbus85VIF29		OBJECT-TYPE
			SYNTAX	INTEGER
			MAX-ACCESS	read-only
			STATUS	current
			::= { hmWanMbus85 88 }

hmWanMbus85Value29		OBJECT-TYPE
			SYNTAX	INTEGER
			MAX-ACCESS	read-only
			STATUS	current
			::= { hmWanMbus85 89 }

hmWanMbus85VIF2A		OBJECT-TYPE
			SYNTAX	INTEGER
			MAX-ACCESS	read-only
			STATUS	current
			::= { hmWanMbus85 90 }

hmWanMbus85Value2A		OBJECT-TYPE
			SYNTAX	INTEGER
			MAX-ACCESS	read-only
			STATUS	current
			::= { hmWanMbus85 91 }

hmWanMbus85VIF2B		OBJECT-TYPE
			SYNTAX	INTEGER
			MAX-ACCESS	read-only
			STATUS	current
			::= { hmWanMbus85 92 }

hmWanMbus85Value2B		OBJECT-TYPE
			SYNTAX	INTEGER
			MAX-ACCESS	read-only
			STATUS	current
			::= { hmWanMbus85 93 }

hmWanMbus85VIF2C		OBJECT-TYPE
			SYNTAX	INTEGER
			MAX-ACCESS	read-only
			STATUS	current
			::= { hmWanMbus85 94 }

hmWanMbus85Value2C		OBJECT-TYPE
			SYNTAX	INTEGER
			MAX-ACCESS	read-only
			STATUS	current
			::= { hmWanMbus85 95 }

hmWanMbus85VIF2D		OBJECT-TYPE
			SYNTAX	INTEGER
			MAX-ACCESS	read-only
			STATUS	current
			::= { hmWanMbus85 96 }

hmWanMbus85Value2D		OBJECT-TYPE
			SYNTAX	INTEGER
			MAX-ACCESS	read-only
			STATUS	current
			::= { hmWanMbus85 97 }

hmWanMbus85VIF2E		OBJECT-TYPE
			SYNTAX	INTEGER
			MAX-ACCESS	read-only
			STATUS	current
			::= { hmWanMbus85 98 }

hmWanMbus85Value2E		OBJECT-TYPE
			SYNTAX	INTEGER
			MAX-ACCESS	read-only
			STATUS	current
			::= { hmWanMbus85 99 }

hmWanMbus85VIF2F		OBJECT-TYPE
			SYNTAX	INTEGER
			MAX-ACCESS	read-only
			STATUS	current
			::= { hmWanMbus85 100 }

hmWanMbus85Value2F		OBJECT-TYPE
			SYNTAX	INTEGER
			MAX-ACCESS	read-only
			STATUS	current
			::= { hmWanMbus85 101 }

hmWanMbus86			OBJECT IDENTIFIER ::= { hmWanMbus 134 }

hmWanMbus86IdNumber		OBJECT-TYPE
			SYNTAX	Gauge32
			MAX-ACCESS	read-only
			STATUS	current
			::= { hmWanMbus86 1 }

hmWanMbus86Manufacturer	OBJECT-TYPE
			SYNTAX	Gauge32
			MAX-ACCESS	read-only
			STATUS	current
			::= { hmWanMbus86 2 }

hmWanMbus86Version		OBJECT-TYPE
			SYNTAX	Gauge32
			MAX-ACCESS	read-only
			STATUS	current
			::= { hmWanMbus86 3 }

hmWanMbus86Medium		OBJECT-TYPE
			SYNTAX	Gauge32
			MAX-ACCESS	read-only
			STATUS	current
			::= { hmWanMbus86 4 }

hmWanMbus86Status		OBJECT-TYPE
			SYNTAX	Gauge32
			MAX-ACCESS	read-only
			STATUS	current
			::= { hmWanMbus86 5 }

hmWanMbus86VIF00		OBJECT-TYPE
			SYNTAX	INTEGER
			MAX-ACCESS	read-only
			STATUS	current
			::= { hmWanMbus86 6 }

hmWanMbus86Value00		OBJECT-TYPE
			SYNTAX	INTEGER
			MAX-ACCESS	read-only
			STATUS	current
			::= { hmWanMbus86 7 }

hmWanMbus86VIF01		OBJECT-TYPE
			SYNTAX	INTEGER
			MAX-ACCESS	read-only
			STATUS	current
			::= { hmWanMbus86 8 }

hmWanMbus86Value01		OBJECT-TYPE
			SYNTAX	INTEGER
			MAX-ACCESS	read-only
			STATUS	current
			::= { hmWanMbus86 9 }

hmWanMbus86VIF02		OBJECT-TYPE
			SYNTAX	INTEGER
			MAX-ACCESS	read-only
			STATUS	current
			::= { hmWanMbus86 10 }

hmWanMbus86Value02		OBJECT-TYPE
			SYNTAX	INTEGER
			MAX-ACCESS	read-only
			STATUS	current
			::= { hmWanMbus86 11 }

hmWanMbus86VIF03		OBJECT-TYPE
			SYNTAX	INTEGER
			MAX-ACCESS	read-only
			STATUS	current
			::= { hmWanMbus86 12 }

hmWanMbus86Value03		OBJECT-TYPE
			SYNTAX	INTEGER
			MAX-ACCESS	read-only
			STATUS	current
			::= { hmWanMbus86 13 }

hmWanMbus86VIF04		OBJECT-TYPE
			SYNTAX	INTEGER
			MAX-ACCESS	read-only
			STATUS	current
			::= { hmWanMbus86 14 }

hmWanMbus86Value04		OBJECT-TYPE
			SYNTAX	INTEGER
			MAX-ACCESS	read-only
			STATUS	current
			::= { hmWanMbus86 15 }

hmWanMbus86VIF05		OBJECT-TYPE
			SYNTAX	INTEGER
			MAX-ACCESS	read-only
			STATUS	current
			::= { hmWanMbus86 16 }

hmWanMbus86Value05		OBJECT-TYPE
			SYNTAX	INTEGER
			MAX-ACCESS	read-only
			STATUS	current
			::= { hmWanMbus86 17 }

hmWanMbus86VIF06		OBJECT-TYPE
			SYNTAX	INTEGER
			MAX-ACCESS	read-only
			STATUS	current
			::= { hmWanMbus86 18 }

hmWanMbus86Value06		OBJECT-TYPE
			SYNTAX	INTEGER
			MAX-ACCESS	read-only
			STATUS	current
			::= { hmWanMbus86 19 }

hmWanMbus86VIF07		OBJECT-TYPE
			SYNTAX	INTEGER
			MAX-ACCESS	read-only
			STATUS	current
			::= { hmWanMbus86 20 }

hmWanMbus86Value07		OBJECT-TYPE
			SYNTAX	INTEGER
			MAX-ACCESS	read-only
			STATUS	current
			::= { hmWanMbus86 21 }

hmWanMbus86VIF08		OBJECT-TYPE
			SYNTAX	INTEGER
			MAX-ACCESS	read-only
			STATUS	current
			::= { hmWanMbus86 22 }

hmWanMbus86Value08		OBJECT-TYPE
			SYNTAX	INTEGER
			MAX-ACCESS	read-only
			STATUS	current
			::= { hmWanMbus86 23 }

hmWanMbus86VIF09		OBJECT-TYPE
			SYNTAX	INTEGER
			MAX-ACCESS	read-only
			STATUS	current
			::= { hmWanMbus86 24 }

hmWanMbus86Value09		OBJECT-TYPE
			SYNTAX	INTEGER
			MAX-ACCESS	read-only
			STATUS	current
			::= { hmWanMbus86 25 }

hmWanMbus86VIF0A		OBJECT-TYPE
			SYNTAX	INTEGER
			MAX-ACCESS	read-only
			STATUS	current
			::= { hmWanMbus86 26 }

hmWanMbus86Value0A		OBJECT-TYPE
			SYNTAX	INTEGER
			MAX-ACCESS	read-only
			STATUS	current
			::= { hmWanMbus86 27 }

hmWanMbus86VIF0B		OBJECT-TYPE
			SYNTAX	INTEGER
			MAX-ACCESS	read-only
			STATUS	current
			::= { hmWanMbus86 28 }

hmWanMbus86Value0B		OBJECT-TYPE
			SYNTAX	INTEGER
			MAX-ACCESS	read-only
			STATUS	current
			::= { hmWanMbus86 29 }

hmWanMbus86VIF0C		OBJECT-TYPE
			SYNTAX	INTEGER
			MAX-ACCESS	read-only
			STATUS	current
			::= { hmWanMbus86 30 }

hmWanMbus86Value0C		OBJECT-TYPE
			SYNTAX	INTEGER
			MAX-ACCESS	read-only
			STATUS	current
			::= { hmWanMbus86 31 }

hmWanMbus86VIF0D		OBJECT-TYPE
			SYNTAX	INTEGER
			MAX-ACCESS	read-only
			STATUS	current
			::= { hmWanMbus86 32 }

hmWanMbus86Value0D		OBJECT-TYPE
			SYNTAX	INTEGER
			MAX-ACCESS	read-only
			STATUS	current
			::= { hmWanMbus86 33 }

hmWanMbus86VIF0E		OBJECT-TYPE
			SYNTAX	INTEGER
			MAX-ACCESS	read-only
			STATUS	current
			::= { hmWanMbus86 34 }

hmWanMbus86Value0E		OBJECT-TYPE
			SYNTAX	INTEGER
			MAX-ACCESS	read-only
			STATUS	current
			::= { hmWanMbus86 35 }

hmWanMbus86VIF0F		OBJECT-TYPE
			SYNTAX	INTEGER
			MAX-ACCESS	read-only
			STATUS	current
			::= { hmWanMbus86 36 }

hmWanMbus86Value0F		OBJECT-TYPE
			SYNTAX	INTEGER
			MAX-ACCESS	read-only
			STATUS	current
			::= { hmWanMbus86 37 }

hmWanMbus86VIF10		OBJECT-TYPE
			SYNTAX	INTEGER
			MAX-ACCESS	read-only
			STATUS	current
			::= { hmWanMbus86 38 }

hmWanMbus86Value10		OBJECT-TYPE
			SYNTAX	INTEGER
			MAX-ACCESS	read-only
			STATUS	current
			::= { hmWanMbus86 39 }

hmWanMbus86VIF11		OBJECT-TYPE
			SYNTAX	INTEGER
			MAX-ACCESS	read-only
			STATUS	current
			::= { hmWanMbus86 40 }

hmWanMbus86Value11		OBJECT-TYPE
			SYNTAX	INTEGER
			MAX-ACCESS	read-only
			STATUS	current
			::= { hmWanMbus86 41 }

hmWanMbus86VIF12		OBJECT-TYPE
			SYNTAX	INTEGER
			MAX-ACCESS	read-only
			STATUS	current
			::= { hmWanMbus86 42 }

hmWanMbus86Value12		OBJECT-TYPE
			SYNTAX	INTEGER
			MAX-ACCESS	read-only
			STATUS	current
			::= { hmWanMbus86 43 }

hmWanMbus86VIF13		OBJECT-TYPE
			SYNTAX	INTEGER
			MAX-ACCESS	read-only
			STATUS	current
			::= { hmWanMbus86 44 }

hmWanMbus86Value13		OBJECT-TYPE
			SYNTAX	INTEGER
			MAX-ACCESS	read-only
			STATUS	current
			::= { hmWanMbus86 45 }

hmWanMbus86VIF14		OBJECT-TYPE
			SYNTAX	INTEGER
			MAX-ACCESS	read-only
			STATUS	current
			::= { hmWanMbus86 46 }

hmWanMbus86Value14		OBJECT-TYPE
			SYNTAX	INTEGER
			MAX-ACCESS	read-only
			STATUS	current
			::= { hmWanMbus86 47 }

hmWanMbus86VIF15		OBJECT-TYPE
			SYNTAX	INTEGER
			MAX-ACCESS	read-only
			STATUS	current
			::= { hmWanMbus86 48 }

hmWanMbus86Value15		OBJECT-TYPE
			SYNTAX	INTEGER
			MAX-ACCESS	read-only
			STATUS	current
			::= { hmWanMbus86 49 }

hmWanMbus86VIF16		OBJECT-TYPE
			SYNTAX	INTEGER
			MAX-ACCESS	read-only
			STATUS	current
			::= { hmWanMbus86 50 }

hmWanMbus86Value16		OBJECT-TYPE
			SYNTAX	INTEGER
			MAX-ACCESS	read-only
			STATUS	current
			::= { hmWanMbus86 51 }

hmWanMbus86VIF17		OBJECT-TYPE
			SYNTAX	INTEGER
			MAX-ACCESS	read-only
			STATUS	current
			::= { hmWanMbus86 52 }

hmWanMbus86Value17		OBJECT-TYPE
			SYNTAX	INTEGER
			MAX-ACCESS	read-only
			STATUS	current
			::= { hmWanMbus86 53 }

hmWanMbus86VIF18		OBJECT-TYPE
			SYNTAX	INTEGER
			MAX-ACCESS	read-only
			STATUS	current
			::= { hmWanMbus86 54 }

hmWanMbus86Value18		OBJECT-TYPE
			SYNTAX	INTEGER
			MAX-ACCESS	read-only
			STATUS	current
			::= { hmWanMbus86 55 }

hmWanMbus86VIF19		OBJECT-TYPE
			SYNTAX	INTEGER
			MAX-ACCESS	read-only
			STATUS	current
			::= { hmWanMbus86 56 }

hmWanMbus86Value19		OBJECT-TYPE
			SYNTAX	INTEGER
			MAX-ACCESS	read-only
			STATUS	current
			::= { hmWanMbus86 57 }

hmWanMbus86VIF1A		OBJECT-TYPE
			SYNTAX	INTEGER
			MAX-ACCESS	read-only
			STATUS	current
			::= { hmWanMbus86 58 }

hmWanMbus86Value1A		OBJECT-TYPE
			SYNTAX	INTEGER
			MAX-ACCESS	read-only
			STATUS	current
			::= { hmWanMbus86 59 }

hmWanMbus86VIF1B		OBJECT-TYPE
			SYNTAX	INTEGER
			MAX-ACCESS	read-only
			STATUS	current
			::= { hmWanMbus86 60 }

hmWanMbus86Value1B		OBJECT-TYPE
			SYNTAX	INTEGER
			MAX-ACCESS	read-only
			STATUS	current
			::= { hmWanMbus86 61 }

hmWanMbus86VIF1C		OBJECT-TYPE
			SYNTAX	INTEGER
			MAX-ACCESS	read-only
			STATUS	current
			::= { hmWanMbus86 62 }

hmWanMbus86Value1C		OBJECT-TYPE
			SYNTAX	INTEGER
			MAX-ACCESS	read-only
			STATUS	current
			::= { hmWanMbus86 63 }

hmWanMbus86VIF1D		OBJECT-TYPE
			SYNTAX	INTEGER
			MAX-ACCESS	read-only
			STATUS	current
			::= { hmWanMbus86 64 }

hmWanMbus86Value1D		OBJECT-TYPE
			SYNTAX	INTEGER
			MAX-ACCESS	read-only
			STATUS	current
			::= { hmWanMbus86 65 }

hmWanMbus86VIF1E		OBJECT-TYPE
			SYNTAX	INTEGER
			MAX-ACCESS	read-only
			STATUS	current
			::= { hmWanMbus86 66 }

hmWanMbus86Value1E		OBJECT-TYPE
			SYNTAX	INTEGER
			MAX-ACCESS	read-only
			STATUS	current
			::= { hmWanMbus86 67 }

hmWanMbus86VIF1F		OBJECT-TYPE
			SYNTAX	INTEGER
			MAX-ACCESS	read-only
			STATUS	current
			::= { hmWanMbus86 68 }

hmWanMbus86Value1F		OBJECT-TYPE
			SYNTAX	INTEGER
			MAX-ACCESS	read-only
			STATUS	current
			::= { hmWanMbus86 69 }

hmWanMbus86VIF20		OBJECT-TYPE
			SYNTAX	INTEGER
			MAX-ACCESS	read-only
			STATUS	current
			::= { hmWanMbus86 70 }

hmWanMbus86Value20		OBJECT-TYPE
			SYNTAX	INTEGER
			MAX-ACCESS	read-only
			STATUS	current
			::= { hmWanMbus86 71 }

hmWanMbus86VIF21		OBJECT-TYPE
			SYNTAX	INTEGER
			MAX-ACCESS	read-only
			STATUS	current
			::= { hmWanMbus86 72 }

hmWanMbus86Value21		OBJECT-TYPE
			SYNTAX	INTEGER
			MAX-ACCESS	read-only
			STATUS	current
			::= { hmWanMbus86 73 }

hmWanMbus86VIF22		OBJECT-TYPE
			SYNTAX	INTEGER
			MAX-ACCESS	read-only
			STATUS	current
			::= { hmWanMbus86 74 }

hmWanMbus86Value22		OBJECT-TYPE
			SYNTAX	INTEGER
			MAX-ACCESS	read-only
			STATUS	current
			::= { hmWanMbus86 75 }

hmWanMbus86VIF23		OBJECT-TYPE
			SYNTAX	INTEGER
			MAX-ACCESS	read-only
			STATUS	current
			::= { hmWanMbus86 76 }

hmWanMbus86Value23		OBJECT-TYPE
			SYNTAX	INTEGER
			MAX-ACCESS	read-only
			STATUS	current
			::= { hmWanMbus86 77 }

hmWanMbus86VIF24		OBJECT-TYPE
			SYNTAX	INTEGER
			MAX-ACCESS	read-only
			STATUS	current
			::= { hmWanMbus86 78 }

hmWanMbus86Value24		OBJECT-TYPE
			SYNTAX	INTEGER
			MAX-ACCESS	read-only
			STATUS	current
			::= { hmWanMbus86 79 }

hmWanMbus86VIF25		OBJECT-TYPE
			SYNTAX	INTEGER
			MAX-ACCESS	read-only
			STATUS	current
			::= { hmWanMbus86 80 }

hmWanMbus86Value25		OBJECT-TYPE
			SYNTAX	INTEGER
			MAX-ACCESS	read-only
			STATUS	current
			::= { hmWanMbus86 81 }

hmWanMbus86VIF26		OBJECT-TYPE
			SYNTAX	INTEGER
			MAX-ACCESS	read-only
			STATUS	current
			::= { hmWanMbus86 82 }

hmWanMbus86Value26		OBJECT-TYPE
			SYNTAX	INTEGER
			MAX-ACCESS	read-only
			STATUS	current
			::= { hmWanMbus86 83 }

hmWanMbus86VIF27		OBJECT-TYPE
			SYNTAX	INTEGER
			MAX-ACCESS	read-only
			STATUS	current
			::= { hmWanMbus86 84 }

hmWanMbus86Value27		OBJECT-TYPE
			SYNTAX	INTEGER
			MAX-ACCESS	read-only
			STATUS	current
			::= { hmWanMbus86 85 }

hmWanMbus86VIF28		OBJECT-TYPE
			SYNTAX	INTEGER
			MAX-ACCESS	read-only
			STATUS	current
			::= { hmWanMbus86 86 }

hmWanMbus86Value28		OBJECT-TYPE
			SYNTAX	INTEGER
			MAX-ACCESS	read-only
			STATUS	current
			::= { hmWanMbus86 87 }

hmWanMbus86VIF29		OBJECT-TYPE
			SYNTAX	INTEGER
			MAX-ACCESS	read-only
			STATUS	current
			::= { hmWanMbus86 88 }

hmWanMbus86Value29		OBJECT-TYPE
			SYNTAX	INTEGER
			MAX-ACCESS	read-only
			STATUS	current
			::= { hmWanMbus86 89 }

hmWanMbus86VIF2A		OBJECT-TYPE
			SYNTAX	INTEGER
			MAX-ACCESS	read-only
			STATUS	current
			::= { hmWanMbus86 90 }

hmWanMbus86Value2A		OBJECT-TYPE
			SYNTAX	INTEGER
			MAX-ACCESS	read-only
			STATUS	current
			::= { hmWanMbus86 91 }

hmWanMbus86VIF2B		OBJECT-TYPE
			SYNTAX	INTEGER
			MAX-ACCESS	read-only
			STATUS	current
			::= { hmWanMbus86 92 }

hmWanMbus86Value2B		OBJECT-TYPE
			SYNTAX	INTEGER
			MAX-ACCESS	read-only
			STATUS	current
			::= { hmWanMbus86 93 }

hmWanMbus86VIF2C		OBJECT-TYPE
			SYNTAX	INTEGER
			MAX-ACCESS	read-only
			STATUS	current
			::= { hmWanMbus86 94 }

hmWanMbus86Value2C		OBJECT-TYPE
			SYNTAX	INTEGER
			MAX-ACCESS	read-only
			STATUS	current
			::= { hmWanMbus86 95 }

hmWanMbus86VIF2D		OBJECT-TYPE
			SYNTAX	INTEGER
			MAX-ACCESS	read-only
			STATUS	current
			::= { hmWanMbus86 96 }

hmWanMbus86Value2D		OBJECT-TYPE
			SYNTAX	INTEGER
			MAX-ACCESS	read-only
			STATUS	current
			::= { hmWanMbus86 97 }

hmWanMbus86VIF2E		OBJECT-TYPE
			SYNTAX	INTEGER
			MAX-ACCESS	read-only
			STATUS	current
			::= { hmWanMbus86 98 }

hmWanMbus86Value2E		OBJECT-TYPE
			SYNTAX	INTEGER
			MAX-ACCESS	read-only
			STATUS	current
			::= { hmWanMbus86 99 }

hmWanMbus86VIF2F		OBJECT-TYPE
			SYNTAX	INTEGER
			MAX-ACCESS	read-only
			STATUS	current
			::= { hmWanMbus86 100 }

hmWanMbus86Value2F		OBJECT-TYPE
			SYNTAX	INTEGER
			MAX-ACCESS	read-only
			STATUS	current
			::= { hmWanMbus86 101 }

hmWanMbus87			OBJECT IDENTIFIER ::= { hmWanMbus 135 }

hmWanMbus87IdNumber		OBJECT-TYPE
			SYNTAX	Gauge32
			MAX-ACCESS	read-only
			STATUS	current
			::= { hmWanMbus87 1 }

hmWanMbus87Manufacturer	OBJECT-TYPE
			SYNTAX	Gauge32
			MAX-ACCESS	read-only
			STATUS	current
			::= { hmWanMbus87 2 }

hmWanMbus87Version		OBJECT-TYPE
			SYNTAX	Gauge32
			MAX-ACCESS	read-only
			STATUS	current
			::= { hmWanMbus87 3 }

hmWanMbus87Medium		OBJECT-TYPE
			SYNTAX	Gauge32
			MAX-ACCESS	read-only
			STATUS	current
			::= { hmWanMbus87 4 }

hmWanMbus87Status		OBJECT-TYPE
			SYNTAX	Gauge32
			MAX-ACCESS	read-only
			STATUS	current
			::= { hmWanMbus87 5 }

hmWanMbus87VIF00		OBJECT-TYPE
			SYNTAX	INTEGER
			MAX-ACCESS	read-only
			STATUS	current
			::= { hmWanMbus87 6 }

hmWanMbus87Value00		OBJECT-TYPE
			SYNTAX	INTEGER
			MAX-ACCESS	read-only
			STATUS	current
			::= { hmWanMbus87 7 }

hmWanMbus87VIF01		OBJECT-TYPE
			SYNTAX	INTEGER
			MAX-ACCESS	read-only
			STATUS	current
			::= { hmWanMbus87 8 }

hmWanMbus87Value01		OBJECT-TYPE
			SYNTAX	INTEGER
			MAX-ACCESS	read-only
			STATUS	current
			::= { hmWanMbus87 9 }

hmWanMbus87VIF02		OBJECT-TYPE
			SYNTAX	INTEGER
			MAX-ACCESS	read-only
			STATUS	current
			::= { hmWanMbus87 10 }

hmWanMbus87Value02		OBJECT-TYPE
			SYNTAX	INTEGER
			MAX-ACCESS	read-only
			STATUS	current
			::= { hmWanMbus87 11 }

hmWanMbus87VIF03		OBJECT-TYPE
			SYNTAX	INTEGER
			MAX-ACCESS	read-only
			STATUS	current
			::= { hmWanMbus87 12 }

hmWanMbus87Value03		OBJECT-TYPE
			SYNTAX	INTEGER
			MAX-ACCESS	read-only
			STATUS	current
			::= { hmWanMbus87 13 }

hmWanMbus87VIF04		OBJECT-TYPE
			SYNTAX	INTEGER
			MAX-ACCESS	read-only
			STATUS	current
			::= { hmWanMbus87 14 }

hmWanMbus87Value04		OBJECT-TYPE
			SYNTAX	INTEGER
			MAX-ACCESS	read-only
			STATUS	current
			::= { hmWanMbus87 15 }

hmWanMbus87VIF05		OBJECT-TYPE
			SYNTAX	INTEGER
			MAX-ACCESS	read-only
			STATUS	current
			::= { hmWanMbus87 16 }

hmWanMbus87Value05		OBJECT-TYPE
			SYNTAX	INTEGER
			MAX-ACCESS	read-only
			STATUS	current
			::= { hmWanMbus87 17 }

hmWanMbus87VIF06		OBJECT-TYPE
			SYNTAX	INTEGER
			MAX-ACCESS	read-only
			STATUS	current
			::= { hmWanMbus87 18 }

hmWanMbus87Value06		OBJECT-TYPE
			SYNTAX	INTEGER
			MAX-ACCESS	read-only
			STATUS	current
			::= { hmWanMbus87 19 }

hmWanMbus87VIF07		OBJECT-TYPE
			SYNTAX	INTEGER
			MAX-ACCESS	read-only
			STATUS	current
			::= { hmWanMbus87 20 }

hmWanMbus87Value07		OBJECT-TYPE
			SYNTAX	INTEGER
			MAX-ACCESS	read-only
			STATUS	current
			::= { hmWanMbus87 21 }

hmWanMbus87VIF08		OBJECT-TYPE
			SYNTAX	INTEGER
			MAX-ACCESS	read-only
			STATUS	current
			::= { hmWanMbus87 22 }

hmWanMbus87Value08		OBJECT-TYPE
			SYNTAX	INTEGER
			MAX-ACCESS	read-only
			STATUS	current
			::= { hmWanMbus87 23 }

hmWanMbus87VIF09		OBJECT-TYPE
			SYNTAX	INTEGER
			MAX-ACCESS	read-only
			STATUS	current
			::= { hmWanMbus87 24 }

hmWanMbus87Value09		OBJECT-TYPE
			SYNTAX	INTEGER
			MAX-ACCESS	read-only
			STATUS	current
			::= { hmWanMbus87 25 }

hmWanMbus87VIF0A		OBJECT-TYPE
			SYNTAX	INTEGER
			MAX-ACCESS	read-only
			STATUS	current
			::= { hmWanMbus87 26 }

hmWanMbus87Value0A		OBJECT-TYPE
			SYNTAX	INTEGER
			MAX-ACCESS	read-only
			STATUS	current
			::= { hmWanMbus87 27 }

hmWanMbus87VIF0B		OBJECT-TYPE
			SYNTAX	INTEGER
			MAX-ACCESS	read-only
			STATUS	current
			::= { hmWanMbus87 28 }

hmWanMbus87Value0B		OBJECT-TYPE
			SYNTAX	INTEGER
			MAX-ACCESS	read-only
			STATUS	current
			::= { hmWanMbus87 29 }

hmWanMbus87VIF0C		OBJECT-TYPE
			SYNTAX	INTEGER
			MAX-ACCESS	read-only
			STATUS	current
			::= { hmWanMbus87 30 }

hmWanMbus87Value0C		OBJECT-TYPE
			SYNTAX	INTEGER
			MAX-ACCESS	read-only
			STATUS	current
			::= { hmWanMbus87 31 }

hmWanMbus87VIF0D		OBJECT-TYPE
			SYNTAX	INTEGER
			MAX-ACCESS	read-only
			STATUS	current
			::= { hmWanMbus87 32 }

hmWanMbus87Value0D		OBJECT-TYPE
			SYNTAX	INTEGER
			MAX-ACCESS	read-only
			STATUS	current
			::= { hmWanMbus87 33 }

hmWanMbus87VIF0E		OBJECT-TYPE
			SYNTAX	INTEGER
			MAX-ACCESS	read-only
			STATUS	current
			::= { hmWanMbus87 34 }

hmWanMbus87Value0E		OBJECT-TYPE
			SYNTAX	INTEGER
			MAX-ACCESS	read-only
			STATUS	current
			::= { hmWanMbus87 35 }

hmWanMbus87VIF0F		OBJECT-TYPE
			SYNTAX	INTEGER
			MAX-ACCESS	read-only
			STATUS	current
			::= { hmWanMbus87 36 }

hmWanMbus87Value0F		OBJECT-TYPE
			SYNTAX	INTEGER
			MAX-ACCESS	read-only
			STATUS	current
			::= { hmWanMbus87 37 }

hmWanMbus87VIF10		OBJECT-TYPE
			SYNTAX	INTEGER
			MAX-ACCESS	read-only
			STATUS	current
			::= { hmWanMbus87 38 }

hmWanMbus87Value10		OBJECT-TYPE
			SYNTAX	INTEGER
			MAX-ACCESS	read-only
			STATUS	current
			::= { hmWanMbus87 39 }

hmWanMbus87VIF11		OBJECT-TYPE
			SYNTAX	INTEGER
			MAX-ACCESS	read-only
			STATUS	current
			::= { hmWanMbus87 40 }

hmWanMbus87Value11		OBJECT-TYPE
			SYNTAX	INTEGER
			MAX-ACCESS	read-only
			STATUS	current
			::= { hmWanMbus87 41 }

hmWanMbus87VIF12		OBJECT-TYPE
			SYNTAX	INTEGER
			MAX-ACCESS	read-only
			STATUS	current
			::= { hmWanMbus87 42 }

hmWanMbus87Value12		OBJECT-TYPE
			SYNTAX	INTEGER
			MAX-ACCESS	read-only
			STATUS	current
			::= { hmWanMbus87 43 }

hmWanMbus87VIF13		OBJECT-TYPE
			SYNTAX	INTEGER
			MAX-ACCESS	read-only
			STATUS	current
			::= { hmWanMbus87 44 }

hmWanMbus87Value13		OBJECT-TYPE
			SYNTAX	INTEGER
			MAX-ACCESS	read-only
			STATUS	current
			::= { hmWanMbus87 45 }

hmWanMbus87VIF14		OBJECT-TYPE
			SYNTAX	INTEGER
			MAX-ACCESS	read-only
			STATUS	current
			::= { hmWanMbus87 46 }

hmWanMbus87Value14		OBJECT-TYPE
			SYNTAX	INTEGER
			MAX-ACCESS	read-only
			STATUS	current
			::= { hmWanMbus87 47 }

hmWanMbus87VIF15		OBJECT-TYPE
			SYNTAX	INTEGER
			MAX-ACCESS	read-only
			STATUS	current
			::= { hmWanMbus87 48 }

hmWanMbus87Value15		OBJECT-TYPE
			SYNTAX	INTEGER
			MAX-ACCESS	read-only
			STATUS	current
			::= { hmWanMbus87 49 }

hmWanMbus87VIF16		OBJECT-TYPE
			SYNTAX	INTEGER
			MAX-ACCESS	read-only
			STATUS	current
			::= { hmWanMbus87 50 }

hmWanMbus87Value16		OBJECT-TYPE
			SYNTAX	INTEGER
			MAX-ACCESS	read-only
			STATUS	current
			::= { hmWanMbus87 51 }

hmWanMbus87VIF17		OBJECT-TYPE
			SYNTAX	INTEGER
			MAX-ACCESS	read-only
			STATUS	current
			::= { hmWanMbus87 52 }

hmWanMbus87Value17		OBJECT-TYPE
			SYNTAX	INTEGER
			MAX-ACCESS	read-only
			STATUS	current
			::= { hmWanMbus87 53 }

hmWanMbus87VIF18		OBJECT-TYPE
			SYNTAX	INTEGER
			MAX-ACCESS	read-only
			STATUS	current
			::= { hmWanMbus87 54 }

hmWanMbus87Value18		OBJECT-TYPE
			SYNTAX	INTEGER
			MAX-ACCESS	read-only
			STATUS	current
			::= { hmWanMbus87 55 }

hmWanMbus87VIF19		OBJECT-TYPE
			SYNTAX	INTEGER
			MAX-ACCESS	read-only
			STATUS	current
			::= { hmWanMbus87 56 }

hmWanMbus87Value19		OBJECT-TYPE
			SYNTAX	INTEGER
			MAX-ACCESS	read-only
			STATUS	current
			::= { hmWanMbus87 57 }

hmWanMbus87VIF1A		OBJECT-TYPE
			SYNTAX	INTEGER
			MAX-ACCESS	read-only
			STATUS	current
			::= { hmWanMbus87 58 }

hmWanMbus87Value1A		OBJECT-TYPE
			SYNTAX	INTEGER
			MAX-ACCESS	read-only
			STATUS	current
			::= { hmWanMbus87 59 }

hmWanMbus87VIF1B		OBJECT-TYPE
			SYNTAX	INTEGER
			MAX-ACCESS	read-only
			STATUS	current
			::= { hmWanMbus87 60 }

hmWanMbus87Value1B		OBJECT-TYPE
			SYNTAX	INTEGER
			MAX-ACCESS	read-only
			STATUS	current
			::= { hmWanMbus87 61 }

hmWanMbus87VIF1C		OBJECT-TYPE
			SYNTAX	INTEGER
			MAX-ACCESS	read-only
			STATUS	current
			::= { hmWanMbus87 62 }

hmWanMbus87Value1C		OBJECT-TYPE
			SYNTAX	INTEGER
			MAX-ACCESS	read-only
			STATUS	current
			::= { hmWanMbus87 63 }

hmWanMbus87VIF1D		OBJECT-TYPE
			SYNTAX	INTEGER
			MAX-ACCESS	read-only
			STATUS	current
			::= { hmWanMbus87 64 }

hmWanMbus87Value1D		OBJECT-TYPE
			SYNTAX	INTEGER
			MAX-ACCESS	read-only
			STATUS	current
			::= { hmWanMbus87 65 }

hmWanMbus87VIF1E		OBJECT-TYPE
			SYNTAX	INTEGER
			MAX-ACCESS	read-only
			STATUS	current
			::= { hmWanMbus87 66 }

hmWanMbus87Value1E		OBJECT-TYPE
			SYNTAX	INTEGER
			MAX-ACCESS	read-only
			STATUS	current
			::= { hmWanMbus87 67 }

hmWanMbus87VIF1F		OBJECT-TYPE
			SYNTAX	INTEGER
			MAX-ACCESS	read-only
			STATUS	current
			::= { hmWanMbus87 68 }

hmWanMbus87Value1F		OBJECT-TYPE
			SYNTAX	INTEGER
			MAX-ACCESS	read-only
			STATUS	current
			::= { hmWanMbus87 69 }

hmWanMbus87VIF20		OBJECT-TYPE
			SYNTAX	INTEGER
			MAX-ACCESS	read-only
			STATUS	current
			::= { hmWanMbus87 70 }

hmWanMbus87Value20		OBJECT-TYPE
			SYNTAX	INTEGER
			MAX-ACCESS	read-only
			STATUS	current
			::= { hmWanMbus87 71 }

hmWanMbus87VIF21		OBJECT-TYPE
			SYNTAX	INTEGER
			MAX-ACCESS	read-only
			STATUS	current
			::= { hmWanMbus87 72 }

hmWanMbus87Value21		OBJECT-TYPE
			SYNTAX	INTEGER
			MAX-ACCESS	read-only
			STATUS	current
			::= { hmWanMbus87 73 }

hmWanMbus87VIF22		OBJECT-TYPE
			SYNTAX	INTEGER
			MAX-ACCESS	read-only
			STATUS	current
			::= { hmWanMbus87 74 }

hmWanMbus87Value22		OBJECT-TYPE
			SYNTAX	INTEGER
			MAX-ACCESS	read-only
			STATUS	current
			::= { hmWanMbus87 75 }

hmWanMbus87VIF23		OBJECT-TYPE
			SYNTAX	INTEGER
			MAX-ACCESS	read-only
			STATUS	current
			::= { hmWanMbus87 76 }

hmWanMbus87Value23		OBJECT-TYPE
			SYNTAX	INTEGER
			MAX-ACCESS	read-only
			STATUS	current
			::= { hmWanMbus87 77 }

hmWanMbus87VIF24		OBJECT-TYPE
			SYNTAX	INTEGER
			MAX-ACCESS	read-only
			STATUS	current
			::= { hmWanMbus87 78 }

hmWanMbus87Value24		OBJECT-TYPE
			SYNTAX	INTEGER
			MAX-ACCESS	read-only
			STATUS	current
			::= { hmWanMbus87 79 }

hmWanMbus87VIF25		OBJECT-TYPE
			SYNTAX	INTEGER
			MAX-ACCESS	read-only
			STATUS	current
			::= { hmWanMbus87 80 }

hmWanMbus87Value25		OBJECT-TYPE
			SYNTAX	INTEGER
			MAX-ACCESS	read-only
			STATUS	current
			::= { hmWanMbus87 81 }

hmWanMbus87VIF26		OBJECT-TYPE
			SYNTAX	INTEGER
			MAX-ACCESS	read-only
			STATUS	current
			::= { hmWanMbus87 82 }

hmWanMbus87Value26		OBJECT-TYPE
			SYNTAX	INTEGER
			MAX-ACCESS	read-only
			STATUS	current
			::= { hmWanMbus87 83 }

hmWanMbus87VIF27		OBJECT-TYPE
			SYNTAX	INTEGER
			MAX-ACCESS	read-only
			STATUS	current
			::= { hmWanMbus87 84 }

hmWanMbus87Value27		OBJECT-TYPE
			SYNTAX	INTEGER
			MAX-ACCESS	read-only
			STATUS	current
			::= { hmWanMbus87 85 }

hmWanMbus87VIF28		OBJECT-TYPE
			SYNTAX	INTEGER
			MAX-ACCESS	read-only
			STATUS	current
			::= { hmWanMbus87 86 }

hmWanMbus87Value28		OBJECT-TYPE
			SYNTAX	INTEGER
			MAX-ACCESS	read-only
			STATUS	current
			::= { hmWanMbus87 87 }

hmWanMbus87VIF29		OBJECT-TYPE
			SYNTAX	INTEGER
			MAX-ACCESS	read-only
			STATUS	current
			::= { hmWanMbus87 88 }

hmWanMbus87Value29		OBJECT-TYPE
			SYNTAX	INTEGER
			MAX-ACCESS	read-only
			STATUS	current
			::= { hmWanMbus87 89 }

hmWanMbus87VIF2A		OBJECT-TYPE
			SYNTAX	INTEGER
			MAX-ACCESS	read-only
			STATUS	current
			::= { hmWanMbus87 90 }

hmWanMbus87Value2A		OBJECT-TYPE
			SYNTAX	INTEGER
			MAX-ACCESS	read-only
			STATUS	current
			::= { hmWanMbus87 91 }

hmWanMbus87VIF2B		OBJECT-TYPE
			SYNTAX	INTEGER
			MAX-ACCESS	read-only
			STATUS	current
			::= { hmWanMbus87 92 }

hmWanMbus87Value2B		OBJECT-TYPE
			SYNTAX	INTEGER
			MAX-ACCESS	read-only
			STATUS	current
			::= { hmWanMbus87 93 }

hmWanMbus87VIF2C		OBJECT-TYPE
			SYNTAX	INTEGER
			MAX-ACCESS	read-only
			STATUS	current
			::= { hmWanMbus87 94 }

hmWanMbus87Value2C		OBJECT-TYPE
			SYNTAX	INTEGER
			MAX-ACCESS	read-only
			STATUS	current
			::= { hmWanMbus87 95 }

hmWanMbus87VIF2D		OBJECT-TYPE
			SYNTAX	INTEGER
			MAX-ACCESS	read-only
			STATUS	current
			::= { hmWanMbus87 96 }

hmWanMbus87Value2D		OBJECT-TYPE
			SYNTAX	INTEGER
			MAX-ACCESS	read-only
			STATUS	current
			::= { hmWanMbus87 97 }

hmWanMbus87VIF2E		OBJECT-TYPE
			SYNTAX	INTEGER
			MAX-ACCESS	read-only
			STATUS	current
			::= { hmWanMbus87 98 }

hmWanMbus87Value2E		OBJECT-TYPE
			SYNTAX	INTEGER
			MAX-ACCESS	read-only
			STATUS	current
			::= { hmWanMbus87 99 }

hmWanMbus87VIF2F		OBJECT-TYPE
			SYNTAX	INTEGER
			MAX-ACCESS	read-only
			STATUS	current
			::= { hmWanMbus87 100 }

hmWanMbus87Value2F		OBJECT-TYPE
			SYNTAX	INTEGER
			MAX-ACCESS	read-only
			STATUS	current
			::= { hmWanMbus87 101 }

hmWanMbus88			OBJECT IDENTIFIER ::= { hmWanMbus 136 }

hmWanMbus88IdNumber		OBJECT-TYPE
			SYNTAX	Gauge32
			MAX-ACCESS	read-only
			STATUS	current
			::= { hmWanMbus88 1 }

hmWanMbus88Manufacturer	OBJECT-TYPE
			SYNTAX	Gauge32
			MAX-ACCESS	read-only
			STATUS	current
			::= { hmWanMbus88 2 }

hmWanMbus88Version		OBJECT-TYPE
			SYNTAX	Gauge32
			MAX-ACCESS	read-only
			STATUS	current
			::= { hmWanMbus88 3 }

hmWanMbus88Medium		OBJECT-TYPE
			SYNTAX	Gauge32
			MAX-ACCESS	read-only
			STATUS	current
			::= { hmWanMbus88 4 }

hmWanMbus88Status		OBJECT-TYPE
			SYNTAX	Gauge32
			MAX-ACCESS	read-only
			STATUS	current
			::= { hmWanMbus88 5 }

hmWanMbus88VIF00		OBJECT-TYPE
			SYNTAX	INTEGER
			MAX-ACCESS	read-only
			STATUS	current
			::= { hmWanMbus88 6 }

hmWanMbus88Value00		OBJECT-TYPE
			SYNTAX	INTEGER
			MAX-ACCESS	read-only
			STATUS	current
			::= { hmWanMbus88 7 }

hmWanMbus88VIF01		OBJECT-TYPE
			SYNTAX	INTEGER
			MAX-ACCESS	read-only
			STATUS	current
			::= { hmWanMbus88 8 }

hmWanMbus88Value01		OBJECT-TYPE
			SYNTAX	INTEGER
			MAX-ACCESS	read-only
			STATUS	current
			::= { hmWanMbus88 9 }

hmWanMbus88VIF02		OBJECT-TYPE
			SYNTAX	INTEGER
			MAX-ACCESS	read-only
			STATUS	current
			::= { hmWanMbus88 10 }

hmWanMbus88Value02		OBJECT-TYPE
			SYNTAX	INTEGER
			MAX-ACCESS	read-only
			STATUS	current
			::= { hmWanMbus88 11 }

hmWanMbus88VIF03		OBJECT-TYPE
			SYNTAX	INTEGER
			MAX-ACCESS	read-only
			STATUS	current
			::= { hmWanMbus88 12 }

hmWanMbus88Value03		OBJECT-TYPE
			SYNTAX	INTEGER
			MAX-ACCESS	read-only
			STATUS	current
			::= { hmWanMbus88 13 }

hmWanMbus88VIF04		OBJECT-TYPE
			SYNTAX	INTEGER
			MAX-ACCESS	read-only
			STATUS	current
			::= { hmWanMbus88 14 }

hmWanMbus88Value04		OBJECT-TYPE
			SYNTAX	INTEGER
			MAX-ACCESS	read-only
			STATUS	current
			::= { hmWanMbus88 15 }

hmWanMbus88VIF05		OBJECT-TYPE
			SYNTAX	INTEGER
			MAX-ACCESS	read-only
			STATUS	current
			::= { hmWanMbus88 16 }

hmWanMbus88Value05		OBJECT-TYPE
			SYNTAX	INTEGER
			MAX-ACCESS	read-only
			STATUS	current
			::= { hmWanMbus88 17 }

hmWanMbus88VIF06		OBJECT-TYPE
			SYNTAX	INTEGER
			MAX-ACCESS	read-only
			STATUS	current
			::= { hmWanMbus88 18 }

hmWanMbus88Value06		OBJECT-TYPE
			SYNTAX	INTEGER
			MAX-ACCESS	read-only
			STATUS	current
			::= { hmWanMbus88 19 }

hmWanMbus88VIF07		OBJECT-TYPE
			SYNTAX	INTEGER
			MAX-ACCESS	read-only
			STATUS	current
			::= { hmWanMbus88 20 }

hmWanMbus88Value07		OBJECT-TYPE
			SYNTAX	INTEGER
			MAX-ACCESS	read-only
			STATUS	current
			::= { hmWanMbus88 21 }

hmWanMbus88VIF08		OBJECT-TYPE
			SYNTAX	INTEGER
			MAX-ACCESS	read-only
			STATUS	current
			::= { hmWanMbus88 22 }

hmWanMbus88Value08		OBJECT-TYPE
			SYNTAX	INTEGER
			MAX-ACCESS	read-only
			STATUS	current
			::= { hmWanMbus88 23 }

hmWanMbus88VIF09		OBJECT-TYPE
			SYNTAX	INTEGER
			MAX-ACCESS	read-only
			STATUS	current
			::= { hmWanMbus88 24 }

hmWanMbus88Value09		OBJECT-TYPE
			SYNTAX	INTEGER
			MAX-ACCESS	read-only
			STATUS	current
			::= { hmWanMbus88 25 }

hmWanMbus88VIF0A		OBJECT-TYPE
			SYNTAX	INTEGER
			MAX-ACCESS	read-only
			STATUS	current
			::= { hmWanMbus88 26 }

hmWanMbus88Value0A		OBJECT-TYPE
			SYNTAX	INTEGER
			MAX-ACCESS	read-only
			STATUS	current
			::= { hmWanMbus88 27 }

hmWanMbus88VIF0B		OBJECT-TYPE
			SYNTAX	INTEGER
			MAX-ACCESS	read-only
			STATUS	current
			::= { hmWanMbus88 28 }

hmWanMbus88Value0B		OBJECT-TYPE
			SYNTAX	INTEGER
			MAX-ACCESS	read-only
			STATUS	current
			::= { hmWanMbus88 29 }

hmWanMbus88VIF0C		OBJECT-TYPE
			SYNTAX	INTEGER
			MAX-ACCESS	read-only
			STATUS	current
			::= { hmWanMbus88 30 }

hmWanMbus88Value0C		OBJECT-TYPE
			SYNTAX	INTEGER
			MAX-ACCESS	read-only
			STATUS	current
			::= { hmWanMbus88 31 }

hmWanMbus88VIF0D		OBJECT-TYPE
			SYNTAX	INTEGER
			MAX-ACCESS	read-only
			STATUS	current
			::= { hmWanMbus88 32 }

hmWanMbus88Value0D		OBJECT-TYPE
			SYNTAX	INTEGER
			MAX-ACCESS	read-only
			STATUS	current
			::= { hmWanMbus88 33 }

hmWanMbus88VIF0E		OBJECT-TYPE
			SYNTAX	INTEGER
			MAX-ACCESS	read-only
			STATUS	current
			::= { hmWanMbus88 34 }

hmWanMbus88Value0E		OBJECT-TYPE
			SYNTAX	INTEGER
			MAX-ACCESS	read-only
			STATUS	current
			::= { hmWanMbus88 35 }

hmWanMbus88VIF0F		OBJECT-TYPE
			SYNTAX	INTEGER
			MAX-ACCESS	read-only
			STATUS	current
			::= { hmWanMbus88 36 }

hmWanMbus88Value0F		OBJECT-TYPE
			SYNTAX	INTEGER
			MAX-ACCESS	read-only
			STATUS	current
			::= { hmWanMbus88 37 }

hmWanMbus88VIF10		OBJECT-TYPE
			SYNTAX	INTEGER
			MAX-ACCESS	read-only
			STATUS	current
			::= { hmWanMbus88 38 }

hmWanMbus88Value10		OBJECT-TYPE
			SYNTAX	INTEGER
			MAX-ACCESS	read-only
			STATUS	current
			::= { hmWanMbus88 39 }

hmWanMbus88VIF11		OBJECT-TYPE
			SYNTAX	INTEGER
			MAX-ACCESS	read-only
			STATUS	current
			::= { hmWanMbus88 40 }

hmWanMbus88Value11		OBJECT-TYPE
			SYNTAX	INTEGER
			MAX-ACCESS	read-only
			STATUS	current
			::= { hmWanMbus88 41 }

hmWanMbus88VIF12		OBJECT-TYPE
			SYNTAX	INTEGER
			MAX-ACCESS	read-only
			STATUS	current
			::= { hmWanMbus88 42 }

hmWanMbus88Value12		OBJECT-TYPE
			SYNTAX	INTEGER
			MAX-ACCESS	read-only
			STATUS	current
			::= { hmWanMbus88 43 }

hmWanMbus88VIF13		OBJECT-TYPE
			SYNTAX	INTEGER
			MAX-ACCESS	read-only
			STATUS	current
			::= { hmWanMbus88 44 }

hmWanMbus88Value13		OBJECT-TYPE
			SYNTAX	INTEGER
			MAX-ACCESS	read-only
			STATUS	current
			::= { hmWanMbus88 45 }

hmWanMbus88VIF14		OBJECT-TYPE
			SYNTAX	INTEGER
			MAX-ACCESS	read-only
			STATUS	current
			::= { hmWanMbus88 46 }

hmWanMbus88Value14		OBJECT-TYPE
			SYNTAX	INTEGER
			MAX-ACCESS	read-only
			STATUS	current
			::= { hmWanMbus88 47 }

hmWanMbus88VIF15		OBJECT-TYPE
			SYNTAX	INTEGER
			MAX-ACCESS	read-only
			STATUS	current
			::= { hmWanMbus88 48 }

hmWanMbus88Value15		OBJECT-TYPE
			SYNTAX	INTEGER
			MAX-ACCESS	read-only
			STATUS	current
			::= { hmWanMbus88 49 }

hmWanMbus88VIF16		OBJECT-TYPE
			SYNTAX	INTEGER
			MAX-ACCESS	read-only
			STATUS	current
			::= { hmWanMbus88 50 }

hmWanMbus88Value16		OBJECT-TYPE
			SYNTAX	INTEGER
			MAX-ACCESS	read-only
			STATUS	current
			::= { hmWanMbus88 51 }

hmWanMbus88VIF17		OBJECT-TYPE
			SYNTAX	INTEGER
			MAX-ACCESS	read-only
			STATUS	current
			::= { hmWanMbus88 52 }

hmWanMbus88Value17		OBJECT-TYPE
			SYNTAX	INTEGER
			MAX-ACCESS	read-only
			STATUS	current
			::= { hmWanMbus88 53 }

hmWanMbus88VIF18		OBJECT-TYPE
			SYNTAX	INTEGER
			MAX-ACCESS	read-only
			STATUS	current
			::= { hmWanMbus88 54 }

hmWanMbus88Value18		OBJECT-TYPE
			SYNTAX	INTEGER
			MAX-ACCESS	read-only
			STATUS	current
			::= { hmWanMbus88 55 }

hmWanMbus88VIF19		OBJECT-TYPE
			SYNTAX	INTEGER
			MAX-ACCESS	read-only
			STATUS	current
			::= { hmWanMbus88 56 }

hmWanMbus88Value19		OBJECT-TYPE
			SYNTAX	INTEGER
			MAX-ACCESS	read-only
			STATUS	current
			::= { hmWanMbus88 57 }

hmWanMbus88VIF1A		OBJECT-TYPE
			SYNTAX	INTEGER
			MAX-ACCESS	read-only
			STATUS	current
			::= { hmWanMbus88 58 }

hmWanMbus88Value1A		OBJECT-TYPE
			SYNTAX	INTEGER
			MAX-ACCESS	read-only
			STATUS	current
			::= { hmWanMbus88 59 }

hmWanMbus88VIF1B		OBJECT-TYPE
			SYNTAX	INTEGER
			MAX-ACCESS	read-only
			STATUS	current
			::= { hmWanMbus88 60 }

hmWanMbus88Value1B		OBJECT-TYPE
			SYNTAX	INTEGER
			MAX-ACCESS	read-only
			STATUS	current
			::= { hmWanMbus88 61 }

hmWanMbus88VIF1C		OBJECT-TYPE
			SYNTAX	INTEGER
			MAX-ACCESS	read-only
			STATUS	current
			::= { hmWanMbus88 62 }

hmWanMbus88Value1C		OBJECT-TYPE
			SYNTAX	INTEGER
			MAX-ACCESS	read-only
			STATUS	current
			::= { hmWanMbus88 63 }

hmWanMbus88VIF1D		OBJECT-TYPE
			SYNTAX	INTEGER
			MAX-ACCESS	read-only
			STATUS	current
			::= { hmWanMbus88 64 }

hmWanMbus88Value1D		OBJECT-TYPE
			SYNTAX	INTEGER
			MAX-ACCESS	read-only
			STATUS	current
			::= { hmWanMbus88 65 }

hmWanMbus88VIF1E		OBJECT-TYPE
			SYNTAX	INTEGER
			MAX-ACCESS	read-only
			STATUS	current
			::= { hmWanMbus88 66 }

hmWanMbus88Value1E		OBJECT-TYPE
			SYNTAX	INTEGER
			MAX-ACCESS	read-only
			STATUS	current
			::= { hmWanMbus88 67 }

hmWanMbus88VIF1F		OBJECT-TYPE
			SYNTAX	INTEGER
			MAX-ACCESS	read-only
			STATUS	current
			::= { hmWanMbus88 68 }

hmWanMbus88Value1F		OBJECT-TYPE
			SYNTAX	INTEGER
			MAX-ACCESS	read-only
			STATUS	current
			::= { hmWanMbus88 69 }

hmWanMbus88VIF20		OBJECT-TYPE
			SYNTAX	INTEGER
			MAX-ACCESS	read-only
			STATUS	current
			::= { hmWanMbus88 70 }

hmWanMbus88Value20		OBJECT-TYPE
			SYNTAX	INTEGER
			MAX-ACCESS	read-only
			STATUS	current
			::= { hmWanMbus88 71 }

hmWanMbus88VIF21		OBJECT-TYPE
			SYNTAX	INTEGER
			MAX-ACCESS	read-only
			STATUS	current
			::= { hmWanMbus88 72 }

hmWanMbus88Value21		OBJECT-TYPE
			SYNTAX	INTEGER
			MAX-ACCESS	read-only
			STATUS	current
			::= { hmWanMbus88 73 }

hmWanMbus88VIF22		OBJECT-TYPE
			SYNTAX	INTEGER
			MAX-ACCESS	read-only
			STATUS	current
			::= { hmWanMbus88 74 }

hmWanMbus88Value22		OBJECT-TYPE
			SYNTAX	INTEGER
			MAX-ACCESS	read-only
			STATUS	current
			::= { hmWanMbus88 75 }

hmWanMbus88VIF23		OBJECT-TYPE
			SYNTAX	INTEGER
			MAX-ACCESS	read-only
			STATUS	current
			::= { hmWanMbus88 76 }

hmWanMbus88Value23		OBJECT-TYPE
			SYNTAX	INTEGER
			MAX-ACCESS	read-only
			STATUS	current
			::= { hmWanMbus88 77 }

hmWanMbus88VIF24		OBJECT-TYPE
			SYNTAX	INTEGER
			MAX-ACCESS	read-only
			STATUS	current
			::= { hmWanMbus88 78 }

hmWanMbus88Value24		OBJECT-TYPE
			SYNTAX	INTEGER
			MAX-ACCESS	read-only
			STATUS	current
			::= { hmWanMbus88 79 }

hmWanMbus88VIF25		OBJECT-TYPE
			SYNTAX	INTEGER
			MAX-ACCESS	read-only
			STATUS	current
			::= { hmWanMbus88 80 }

hmWanMbus88Value25		OBJECT-TYPE
			SYNTAX	INTEGER
			MAX-ACCESS	read-only
			STATUS	current
			::= { hmWanMbus88 81 }

hmWanMbus88VIF26		OBJECT-TYPE
			SYNTAX	INTEGER
			MAX-ACCESS	read-only
			STATUS	current
			::= { hmWanMbus88 82 }

hmWanMbus88Value26		OBJECT-TYPE
			SYNTAX	INTEGER
			MAX-ACCESS	read-only
			STATUS	current
			::= { hmWanMbus88 83 }

hmWanMbus88VIF27		OBJECT-TYPE
			SYNTAX	INTEGER
			MAX-ACCESS	read-only
			STATUS	current
			::= { hmWanMbus88 84 }

hmWanMbus88Value27		OBJECT-TYPE
			SYNTAX	INTEGER
			MAX-ACCESS	read-only
			STATUS	current
			::= { hmWanMbus88 85 }

hmWanMbus88VIF28		OBJECT-TYPE
			SYNTAX	INTEGER
			MAX-ACCESS	read-only
			STATUS	current
			::= { hmWanMbus88 86 }

hmWanMbus88Value28		OBJECT-TYPE
			SYNTAX	INTEGER
			MAX-ACCESS	read-only
			STATUS	current
			::= { hmWanMbus88 87 }

hmWanMbus88VIF29		OBJECT-TYPE
			SYNTAX	INTEGER
			MAX-ACCESS	read-only
			STATUS	current
			::= { hmWanMbus88 88 }

hmWanMbus88Value29		OBJECT-TYPE
			SYNTAX	INTEGER
			MAX-ACCESS	read-only
			STATUS	current
			::= { hmWanMbus88 89 }

hmWanMbus88VIF2A		OBJECT-TYPE
			SYNTAX	INTEGER
			MAX-ACCESS	read-only
			STATUS	current
			::= { hmWanMbus88 90 }

hmWanMbus88Value2A		OBJECT-TYPE
			SYNTAX	INTEGER
			MAX-ACCESS	read-only
			STATUS	current
			::= { hmWanMbus88 91 }

hmWanMbus88VIF2B		OBJECT-TYPE
			SYNTAX	INTEGER
			MAX-ACCESS	read-only
			STATUS	current
			::= { hmWanMbus88 92 }

hmWanMbus88Value2B		OBJECT-TYPE
			SYNTAX	INTEGER
			MAX-ACCESS	read-only
			STATUS	current
			::= { hmWanMbus88 93 }

hmWanMbus88VIF2C		OBJECT-TYPE
			SYNTAX	INTEGER
			MAX-ACCESS	read-only
			STATUS	current
			::= { hmWanMbus88 94 }

hmWanMbus88Value2C		OBJECT-TYPE
			SYNTAX	INTEGER
			MAX-ACCESS	read-only
			STATUS	current
			::= { hmWanMbus88 95 }

hmWanMbus88VIF2D		OBJECT-TYPE
			SYNTAX	INTEGER
			MAX-ACCESS	read-only
			STATUS	current
			::= { hmWanMbus88 96 }

hmWanMbus88Value2D		OBJECT-TYPE
			SYNTAX	INTEGER
			MAX-ACCESS	read-only
			STATUS	current
			::= { hmWanMbus88 97 }

hmWanMbus88VIF2E		OBJECT-TYPE
			SYNTAX	INTEGER
			MAX-ACCESS	read-only
			STATUS	current
			::= { hmWanMbus88 98 }

hmWanMbus88Value2E		OBJECT-TYPE
			SYNTAX	INTEGER
			MAX-ACCESS	read-only
			STATUS	current
			::= { hmWanMbus88 99 }

hmWanMbus88VIF2F		OBJECT-TYPE
			SYNTAX	INTEGER
			MAX-ACCESS	read-only
			STATUS	current
			::= { hmWanMbus88 100 }

hmWanMbus88Value2F		OBJECT-TYPE
			SYNTAX	INTEGER
			MAX-ACCESS	read-only
			STATUS	current
			::= { hmWanMbus88 101 }

hmWanMbus89			OBJECT IDENTIFIER ::= { hmWanMbus 137 }

hmWanMbus89IdNumber		OBJECT-TYPE
			SYNTAX	Gauge32
			MAX-ACCESS	read-only
			STATUS	current
			::= { hmWanMbus89 1 }

hmWanMbus89Manufacturer	OBJECT-TYPE
			SYNTAX	Gauge32
			MAX-ACCESS	read-only
			STATUS	current
			::= { hmWanMbus89 2 }

hmWanMbus89Version		OBJECT-TYPE
			SYNTAX	Gauge32
			MAX-ACCESS	read-only
			STATUS	current
			::= { hmWanMbus89 3 }

hmWanMbus89Medium		OBJECT-TYPE
			SYNTAX	Gauge32
			MAX-ACCESS	read-only
			STATUS	current
			::= { hmWanMbus89 4 }

hmWanMbus89Status		OBJECT-TYPE
			SYNTAX	Gauge32
			MAX-ACCESS	read-only
			STATUS	current
			::= { hmWanMbus89 5 }

hmWanMbus89VIF00		OBJECT-TYPE
			SYNTAX	INTEGER
			MAX-ACCESS	read-only
			STATUS	current
			::= { hmWanMbus89 6 }

hmWanMbus89Value00		OBJECT-TYPE
			SYNTAX	INTEGER
			MAX-ACCESS	read-only
			STATUS	current
			::= { hmWanMbus89 7 }

hmWanMbus89VIF01		OBJECT-TYPE
			SYNTAX	INTEGER
			MAX-ACCESS	read-only
			STATUS	current
			::= { hmWanMbus89 8 }

hmWanMbus89Value01		OBJECT-TYPE
			SYNTAX	INTEGER
			MAX-ACCESS	read-only
			STATUS	current
			::= { hmWanMbus89 9 }

hmWanMbus89VIF02		OBJECT-TYPE
			SYNTAX	INTEGER
			MAX-ACCESS	read-only
			STATUS	current
			::= { hmWanMbus89 10 }

hmWanMbus89Value02		OBJECT-TYPE
			SYNTAX	INTEGER
			MAX-ACCESS	read-only
			STATUS	current
			::= { hmWanMbus89 11 }

hmWanMbus89VIF03		OBJECT-TYPE
			SYNTAX	INTEGER
			MAX-ACCESS	read-only
			STATUS	current
			::= { hmWanMbus89 12 }

hmWanMbus89Value03		OBJECT-TYPE
			SYNTAX	INTEGER
			MAX-ACCESS	read-only
			STATUS	current
			::= { hmWanMbus89 13 }

hmWanMbus89VIF04		OBJECT-TYPE
			SYNTAX	INTEGER
			MAX-ACCESS	read-only
			STATUS	current
			::= { hmWanMbus89 14 }

hmWanMbus89Value04		OBJECT-TYPE
			SYNTAX	INTEGER
			MAX-ACCESS	read-only
			STATUS	current
			::= { hmWanMbus89 15 }

hmWanMbus89VIF05		OBJECT-TYPE
			SYNTAX	INTEGER
			MAX-ACCESS	read-only
			STATUS	current
			::= { hmWanMbus89 16 }

hmWanMbus89Value05		OBJECT-TYPE
			SYNTAX	INTEGER
			MAX-ACCESS	read-only
			STATUS	current
			::= { hmWanMbus89 17 }

hmWanMbus89VIF06		OBJECT-TYPE
			SYNTAX	INTEGER
			MAX-ACCESS	read-only
			STATUS	current
			::= { hmWanMbus89 18 }

hmWanMbus89Value06		OBJECT-TYPE
			SYNTAX	INTEGER
			MAX-ACCESS	read-only
			STATUS	current
			::= { hmWanMbus89 19 }

hmWanMbus89VIF07		OBJECT-TYPE
			SYNTAX	INTEGER
			MAX-ACCESS	read-only
			STATUS	current
			::= { hmWanMbus89 20 }

hmWanMbus89Value07		OBJECT-TYPE
			SYNTAX	INTEGER
			MAX-ACCESS	read-only
			STATUS	current
			::= { hmWanMbus89 21 }

hmWanMbus89VIF08		OBJECT-TYPE
			SYNTAX	INTEGER
			MAX-ACCESS	read-only
			STATUS	current
			::= { hmWanMbus89 22 }

hmWanMbus89Value08		OBJECT-TYPE
			SYNTAX	INTEGER
			MAX-ACCESS	read-only
			STATUS	current
			::= { hmWanMbus89 23 }

hmWanMbus89VIF09		OBJECT-TYPE
			SYNTAX	INTEGER
			MAX-ACCESS	read-only
			STATUS	current
			::= { hmWanMbus89 24 }

hmWanMbus89Value09		OBJECT-TYPE
			SYNTAX	INTEGER
			MAX-ACCESS	read-only
			STATUS	current
			::= { hmWanMbus89 25 }

hmWanMbus89VIF0A		OBJECT-TYPE
			SYNTAX	INTEGER
			MAX-ACCESS	read-only
			STATUS	current
			::= { hmWanMbus89 26 }

hmWanMbus89Value0A		OBJECT-TYPE
			SYNTAX	INTEGER
			MAX-ACCESS	read-only
			STATUS	current
			::= { hmWanMbus89 27 }

hmWanMbus89VIF0B		OBJECT-TYPE
			SYNTAX	INTEGER
			MAX-ACCESS	read-only
			STATUS	current
			::= { hmWanMbus89 28 }

hmWanMbus89Value0B		OBJECT-TYPE
			SYNTAX	INTEGER
			MAX-ACCESS	read-only
			STATUS	current
			::= { hmWanMbus89 29 }

hmWanMbus89VIF0C		OBJECT-TYPE
			SYNTAX	INTEGER
			MAX-ACCESS	read-only
			STATUS	current
			::= { hmWanMbus89 30 }

hmWanMbus89Value0C		OBJECT-TYPE
			SYNTAX	INTEGER
			MAX-ACCESS	read-only
			STATUS	current
			::= { hmWanMbus89 31 }

hmWanMbus89VIF0D		OBJECT-TYPE
			SYNTAX	INTEGER
			MAX-ACCESS	read-only
			STATUS	current
			::= { hmWanMbus89 32 }

hmWanMbus89Value0D		OBJECT-TYPE
			SYNTAX	INTEGER
			MAX-ACCESS	read-only
			STATUS	current
			::= { hmWanMbus89 33 }

hmWanMbus89VIF0E		OBJECT-TYPE
			SYNTAX	INTEGER
			MAX-ACCESS	read-only
			STATUS	current
			::= { hmWanMbus89 34 }

hmWanMbus89Value0E		OBJECT-TYPE
			SYNTAX	INTEGER
			MAX-ACCESS	read-only
			STATUS	current
			::= { hmWanMbus89 35 }

hmWanMbus89VIF0F		OBJECT-TYPE
			SYNTAX	INTEGER
			MAX-ACCESS	read-only
			STATUS	current
			::= { hmWanMbus89 36 }

hmWanMbus89Value0F		OBJECT-TYPE
			SYNTAX	INTEGER
			MAX-ACCESS	read-only
			STATUS	current
			::= { hmWanMbus89 37 }

hmWanMbus89VIF10		OBJECT-TYPE
			SYNTAX	INTEGER
			MAX-ACCESS	read-only
			STATUS	current
			::= { hmWanMbus89 38 }

hmWanMbus89Value10		OBJECT-TYPE
			SYNTAX	INTEGER
			MAX-ACCESS	read-only
			STATUS	current
			::= { hmWanMbus89 39 }

hmWanMbus89VIF11		OBJECT-TYPE
			SYNTAX	INTEGER
			MAX-ACCESS	read-only
			STATUS	current
			::= { hmWanMbus89 40 }

hmWanMbus89Value11		OBJECT-TYPE
			SYNTAX	INTEGER
			MAX-ACCESS	read-only
			STATUS	current
			::= { hmWanMbus89 41 }

hmWanMbus89VIF12		OBJECT-TYPE
			SYNTAX	INTEGER
			MAX-ACCESS	read-only
			STATUS	current
			::= { hmWanMbus89 42 }

hmWanMbus89Value12		OBJECT-TYPE
			SYNTAX	INTEGER
			MAX-ACCESS	read-only
			STATUS	current
			::= { hmWanMbus89 43 }

hmWanMbus89VIF13		OBJECT-TYPE
			SYNTAX	INTEGER
			MAX-ACCESS	read-only
			STATUS	current
			::= { hmWanMbus89 44 }

hmWanMbus89Value13		OBJECT-TYPE
			SYNTAX	INTEGER
			MAX-ACCESS	read-only
			STATUS	current
			::= { hmWanMbus89 45 }

hmWanMbus89VIF14		OBJECT-TYPE
			SYNTAX	INTEGER
			MAX-ACCESS	read-only
			STATUS	current
			::= { hmWanMbus89 46 }

hmWanMbus89Value14		OBJECT-TYPE
			SYNTAX	INTEGER
			MAX-ACCESS	read-only
			STATUS	current
			::= { hmWanMbus89 47 }

hmWanMbus89VIF15		OBJECT-TYPE
			SYNTAX	INTEGER
			MAX-ACCESS	read-only
			STATUS	current
			::= { hmWanMbus89 48 }

hmWanMbus89Value15		OBJECT-TYPE
			SYNTAX	INTEGER
			MAX-ACCESS	read-only
			STATUS	current
			::= { hmWanMbus89 49 }

hmWanMbus89VIF16		OBJECT-TYPE
			SYNTAX	INTEGER
			MAX-ACCESS	read-only
			STATUS	current
			::= { hmWanMbus89 50 }

hmWanMbus89Value16		OBJECT-TYPE
			SYNTAX	INTEGER
			MAX-ACCESS	read-only
			STATUS	current
			::= { hmWanMbus89 51 }

hmWanMbus89VIF17		OBJECT-TYPE
			SYNTAX	INTEGER
			MAX-ACCESS	read-only
			STATUS	current
			::= { hmWanMbus89 52 }

hmWanMbus89Value17		OBJECT-TYPE
			SYNTAX	INTEGER
			MAX-ACCESS	read-only
			STATUS	current
			::= { hmWanMbus89 53 }

hmWanMbus89VIF18		OBJECT-TYPE
			SYNTAX	INTEGER
			MAX-ACCESS	read-only
			STATUS	current
			::= { hmWanMbus89 54 }

hmWanMbus89Value18		OBJECT-TYPE
			SYNTAX	INTEGER
			MAX-ACCESS	read-only
			STATUS	current
			::= { hmWanMbus89 55 }

hmWanMbus89VIF19		OBJECT-TYPE
			SYNTAX	INTEGER
			MAX-ACCESS	read-only
			STATUS	current
			::= { hmWanMbus89 56 }

hmWanMbus89Value19		OBJECT-TYPE
			SYNTAX	INTEGER
			MAX-ACCESS	read-only
			STATUS	current
			::= { hmWanMbus89 57 }

hmWanMbus89VIF1A		OBJECT-TYPE
			SYNTAX	INTEGER
			MAX-ACCESS	read-only
			STATUS	current
			::= { hmWanMbus89 58 }

hmWanMbus89Value1A		OBJECT-TYPE
			SYNTAX	INTEGER
			MAX-ACCESS	read-only
			STATUS	current
			::= { hmWanMbus89 59 }

hmWanMbus89VIF1B		OBJECT-TYPE
			SYNTAX	INTEGER
			MAX-ACCESS	read-only
			STATUS	current
			::= { hmWanMbus89 60 }

hmWanMbus89Value1B		OBJECT-TYPE
			SYNTAX	INTEGER
			MAX-ACCESS	read-only
			STATUS	current
			::= { hmWanMbus89 61 }

hmWanMbus89VIF1C		OBJECT-TYPE
			SYNTAX	INTEGER
			MAX-ACCESS	read-only
			STATUS	current
			::= { hmWanMbus89 62 }

hmWanMbus89Value1C		OBJECT-TYPE
			SYNTAX	INTEGER
			MAX-ACCESS	read-only
			STATUS	current
			::= { hmWanMbus89 63 }

hmWanMbus89VIF1D		OBJECT-TYPE
			SYNTAX	INTEGER
			MAX-ACCESS	read-only
			STATUS	current
			::= { hmWanMbus89 64 }

hmWanMbus89Value1D		OBJECT-TYPE
			SYNTAX	INTEGER
			MAX-ACCESS	read-only
			STATUS	current
			::= { hmWanMbus89 65 }

hmWanMbus89VIF1E		OBJECT-TYPE
			SYNTAX	INTEGER
			MAX-ACCESS	read-only
			STATUS	current
			::= { hmWanMbus89 66 }

hmWanMbus89Value1E		OBJECT-TYPE
			SYNTAX	INTEGER
			MAX-ACCESS	read-only
			STATUS	current
			::= { hmWanMbus89 67 }

hmWanMbus89VIF1F		OBJECT-TYPE
			SYNTAX	INTEGER
			MAX-ACCESS	read-only
			STATUS	current
			::= { hmWanMbus89 68 }

hmWanMbus89Value1F		OBJECT-TYPE
			SYNTAX	INTEGER
			MAX-ACCESS	read-only
			STATUS	current
			::= { hmWanMbus89 69 }

hmWanMbus89VIF20		OBJECT-TYPE
			SYNTAX	INTEGER
			MAX-ACCESS	read-only
			STATUS	current
			::= { hmWanMbus89 70 }

hmWanMbus89Value20		OBJECT-TYPE
			SYNTAX	INTEGER
			MAX-ACCESS	read-only
			STATUS	current
			::= { hmWanMbus89 71 }

hmWanMbus89VIF21		OBJECT-TYPE
			SYNTAX	INTEGER
			MAX-ACCESS	read-only
			STATUS	current
			::= { hmWanMbus89 72 }

hmWanMbus89Value21		OBJECT-TYPE
			SYNTAX	INTEGER
			MAX-ACCESS	read-only
			STATUS	current
			::= { hmWanMbus89 73 }

hmWanMbus89VIF22		OBJECT-TYPE
			SYNTAX	INTEGER
			MAX-ACCESS	read-only
			STATUS	current
			::= { hmWanMbus89 74 }

hmWanMbus89Value22		OBJECT-TYPE
			SYNTAX	INTEGER
			MAX-ACCESS	read-only
			STATUS	current
			::= { hmWanMbus89 75 }

hmWanMbus89VIF23		OBJECT-TYPE
			SYNTAX	INTEGER
			MAX-ACCESS	read-only
			STATUS	current
			::= { hmWanMbus89 76 }

hmWanMbus89Value23		OBJECT-TYPE
			SYNTAX	INTEGER
			MAX-ACCESS	read-only
			STATUS	current
			::= { hmWanMbus89 77 }

hmWanMbus89VIF24		OBJECT-TYPE
			SYNTAX	INTEGER
			MAX-ACCESS	read-only
			STATUS	current
			::= { hmWanMbus89 78 }

hmWanMbus89Value24		OBJECT-TYPE
			SYNTAX	INTEGER
			MAX-ACCESS	read-only
			STATUS	current
			::= { hmWanMbus89 79 }

hmWanMbus89VIF25		OBJECT-TYPE
			SYNTAX	INTEGER
			MAX-ACCESS	read-only
			STATUS	current
			::= { hmWanMbus89 80 }

hmWanMbus89Value25		OBJECT-TYPE
			SYNTAX	INTEGER
			MAX-ACCESS	read-only
			STATUS	current
			::= { hmWanMbus89 81 }

hmWanMbus89VIF26		OBJECT-TYPE
			SYNTAX	INTEGER
			MAX-ACCESS	read-only
			STATUS	current
			::= { hmWanMbus89 82 }

hmWanMbus89Value26		OBJECT-TYPE
			SYNTAX	INTEGER
			MAX-ACCESS	read-only
			STATUS	current
			::= { hmWanMbus89 83 }

hmWanMbus89VIF27		OBJECT-TYPE
			SYNTAX	INTEGER
			MAX-ACCESS	read-only
			STATUS	current
			::= { hmWanMbus89 84 }

hmWanMbus89Value27		OBJECT-TYPE
			SYNTAX	INTEGER
			MAX-ACCESS	read-only
			STATUS	current
			::= { hmWanMbus89 85 }

hmWanMbus89VIF28		OBJECT-TYPE
			SYNTAX	INTEGER
			MAX-ACCESS	read-only
			STATUS	current
			::= { hmWanMbus89 86 }

hmWanMbus89Value28		OBJECT-TYPE
			SYNTAX	INTEGER
			MAX-ACCESS	read-only
			STATUS	current
			::= { hmWanMbus89 87 }

hmWanMbus89VIF29		OBJECT-TYPE
			SYNTAX	INTEGER
			MAX-ACCESS	read-only
			STATUS	current
			::= { hmWanMbus89 88 }

hmWanMbus89Value29		OBJECT-TYPE
			SYNTAX	INTEGER
			MAX-ACCESS	read-only
			STATUS	current
			::= { hmWanMbus89 89 }

hmWanMbus89VIF2A		OBJECT-TYPE
			SYNTAX	INTEGER
			MAX-ACCESS	read-only
			STATUS	current
			::= { hmWanMbus89 90 }

hmWanMbus89Value2A		OBJECT-TYPE
			SYNTAX	INTEGER
			MAX-ACCESS	read-only
			STATUS	current
			::= { hmWanMbus89 91 }

hmWanMbus89VIF2B		OBJECT-TYPE
			SYNTAX	INTEGER
			MAX-ACCESS	read-only
			STATUS	current
			::= { hmWanMbus89 92 }

hmWanMbus89Value2B		OBJECT-TYPE
			SYNTAX	INTEGER
			MAX-ACCESS	read-only
			STATUS	current
			::= { hmWanMbus89 93 }

hmWanMbus89VIF2C		OBJECT-TYPE
			SYNTAX	INTEGER
			MAX-ACCESS	read-only
			STATUS	current
			::= { hmWanMbus89 94 }

hmWanMbus89Value2C		OBJECT-TYPE
			SYNTAX	INTEGER
			MAX-ACCESS	read-only
			STATUS	current
			::= { hmWanMbus89 95 }

hmWanMbus89VIF2D		OBJECT-TYPE
			SYNTAX	INTEGER
			MAX-ACCESS	read-only
			STATUS	current
			::= { hmWanMbus89 96 }

hmWanMbus89Value2D		OBJECT-TYPE
			SYNTAX	INTEGER
			MAX-ACCESS	read-only
			STATUS	current
			::= { hmWanMbus89 97 }

hmWanMbus89VIF2E		OBJECT-TYPE
			SYNTAX	INTEGER
			MAX-ACCESS	read-only
			STATUS	current
			::= { hmWanMbus89 98 }

hmWanMbus89Value2E		OBJECT-TYPE
			SYNTAX	INTEGER
			MAX-ACCESS	read-only
			STATUS	current
			::= { hmWanMbus89 99 }

hmWanMbus89VIF2F		OBJECT-TYPE
			SYNTAX	INTEGER
			MAX-ACCESS	read-only
			STATUS	current
			::= { hmWanMbus89 100 }

hmWanMbus89Value2F		OBJECT-TYPE
			SYNTAX	INTEGER
			MAX-ACCESS	read-only
			STATUS	current
			::= { hmWanMbus89 101 }

hmWanMbus8A			OBJECT IDENTIFIER ::= { hmWanMbus 138 }

hmWanMbus8AIdNumber		OBJECT-TYPE
			SYNTAX	Gauge32
			MAX-ACCESS	read-only
			STATUS	current
			::= { hmWanMbus8A 1 }

hmWanMbus8AManufacturer	OBJECT-TYPE
			SYNTAX	Gauge32
			MAX-ACCESS	read-only
			STATUS	current
			::= { hmWanMbus8A 2 }

hmWanMbus8AVersion		OBJECT-TYPE
			SYNTAX	Gauge32
			MAX-ACCESS	read-only
			STATUS	current
			::= { hmWanMbus8A 3 }

hmWanMbus8AMedium		OBJECT-TYPE
			SYNTAX	Gauge32
			MAX-ACCESS	read-only
			STATUS	current
			::= { hmWanMbus8A 4 }

hmWanMbus8AStatus		OBJECT-TYPE
			SYNTAX	Gauge32
			MAX-ACCESS	read-only
			STATUS	current
			::= { hmWanMbus8A 5 }

hmWanMbus8AVIF00		OBJECT-TYPE
			SYNTAX	INTEGER
			MAX-ACCESS	read-only
			STATUS	current
			::= { hmWanMbus8A 6 }

hmWanMbus8AValue00		OBJECT-TYPE
			SYNTAX	INTEGER
			MAX-ACCESS	read-only
			STATUS	current
			::= { hmWanMbus8A 7 }

hmWanMbus8AVIF01		OBJECT-TYPE
			SYNTAX	INTEGER
			MAX-ACCESS	read-only
			STATUS	current
			::= { hmWanMbus8A 8 }

hmWanMbus8AValue01		OBJECT-TYPE
			SYNTAX	INTEGER
			MAX-ACCESS	read-only
			STATUS	current
			::= { hmWanMbus8A 9 }

hmWanMbus8AVIF02		OBJECT-TYPE
			SYNTAX	INTEGER
			MAX-ACCESS	read-only
			STATUS	current
			::= { hmWanMbus8A 10 }

hmWanMbus8AValue02		OBJECT-TYPE
			SYNTAX	INTEGER
			MAX-ACCESS	read-only
			STATUS	current
			::= { hmWanMbus8A 11 }

hmWanMbus8AVIF03		OBJECT-TYPE
			SYNTAX	INTEGER
			MAX-ACCESS	read-only
			STATUS	current
			::= { hmWanMbus8A 12 }

hmWanMbus8AValue03		OBJECT-TYPE
			SYNTAX	INTEGER
			MAX-ACCESS	read-only
			STATUS	current
			::= { hmWanMbus8A 13 }

hmWanMbus8AVIF04		OBJECT-TYPE
			SYNTAX	INTEGER
			MAX-ACCESS	read-only
			STATUS	current
			::= { hmWanMbus8A 14 }

hmWanMbus8AValue04		OBJECT-TYPE
			SYNTAX	INTEGER
			MAX-ACCESS	read-only
			STATUS	current
			::= { hmWanMbus8A 15 }

hmWanMbus8AVIF05		OBJECT-TYPE
			SYNTAX	INTEGER
			MAX-ACCESS	read-only
			STATUS	current
			::= { hmWanMbus8A 16 }

hmWanMbus8AValue05		OBJECT-TYPE
			SYNTAX	INTEGER
			MAX-ACCESS	read-only
			STATUS	current
			::= { hmWanMbus8A 17 }

hmWanMbus8AVIF06		OBJECT-TYPE
			SYNTAX	INTEGER
			MAX-ACCESS	read-only
			STATUS	current
			::= { hmWanMbus8A 18 }

hmWanMbus8AValue06		OBJECT-TYPE
			SYNTAX	INTEGER
			MAX-ACCESS	read-only
			STATUS	current
			::= { hmWanMbus8A 19 }

hmWanMbus8AVIF07		OBJECT-TYPE
			SYNTAX	INTEGER
			MAX-ACCESS	read-only
			STATUS	current
			::= { hmWanMbus8A 20 }

hmWanMbus8AValue07		OBJECT-TYPE
			SYNTAX	INTEGER
			MAX-ACCESS	read-only
			STATUS	current
			::= { hmWanMbus8A 21 }

hmWanMbus8AVIF08		OBJECT-TYPE
			SYNTAX	INTEGER
			MAX-ACCESS	read-only
			STATUS	current
			::= { hmWanMbus8A 22 }

hmWanMbus8AValue08		OBJECT-TYPE
			SYNTAX	INTEGER
			MAX-ACCESS	read-only
			STATUS	current
			::= { hmWanMbus8A 23 }

hmWanMbus8AVIF09		OBJECT-TYPE
			SYNTAX	INTEGER
			MAX-ACCESS	read-only
			STATUS	current
			::= { hmWanMbus8A 24 }

hmWanMbus8AValue09		OBJECT-TYPE
			SYNTAX	INTEGER
			MAX-ACCESS	read-only
			STATUS	current
			::= { hmWanMbus8A 25 }

hmWanMbus8AVIF0A		OBJECT-TYPE
			SYNTAX	INTEGER
			MAX-ACCESS	read-only
			STATUS	current
			::= { hmWanMbus8A 26 }

hmWanMbus8AValue0A		OBJECT-TYPE
			SYNTAX	INTEGER
			MAX-ACCESS	read-only
			STATUS	current
			::= { hmWanMbus8A 27 }

hmWanMbus8AVIF0B		OBJECT-TYPE
			SYNTAX	INTEGER
			MAX-ACCESS	read-only
			STATUS	current
			::= { hmWanMbus8A 28 }

hmWanMbus8AValue0B		OBJECT-TYPE
			SYNTAX	INTEGER
			MAX-ACCESS	read-only
			STATUS	current
			::= { hmWanMbus8A 29 }

hmWanMbus8AVIF0C		OBJECT-TYPE
			SYNTAX	INTEGER
			MAX-ACCESS	read-only
			STATUS	current
			::= { hmWanMbus8A 30 }

hmWanMbus8AValue0C		OBJECT-TYPE
			SYNTAX	INTEGER
			MAX-ACCESS	read-only
			STATUS	current
			::= { hmWanMbus8A 31 }

hmWanMbus8AVIF0D		OBJECT-TYPE
			SYNTAX	INTEGER
			MAX-ACCESS	read-only
			STATUS	current
			::= { hmWanMbus8A 32 }

hmWanMbus8AValue0D		OBJECT-TYPE
			SYNTAX	INTEGER
			MAX-ACCESS	read-only
			STATUS	current
			::= { hmWanMbus8A 33 }

hmWanMbus8AVIF0E		OBJECT-TYPE
			SYNTAX	INTEGER
			MAX-ACCESS	read-only
			STATUS	current
			::= { hmWanMbus8A 34 }

hmWanMbus8AValue0E		OBJECT-TYPE
			SYNTAX	INTEGER
			MAX-ACCESS	read-only
			STATUS	current
			::= { hmWanMbus8A 35 }

hmWanMbus8AVIF0F		OBJECT-TYPE
			SYNTAX	INTEGER
			MAX-ACCESS	read-only
			STATUS	current
			::= { hmWanMbus8A 36 }

hmWanMbus8AValue0F		OBJECT-TYPE
			SYNTAX	INTEGER
			MAX-ACCESS	read-only
			STATUS	current
			::= { hmWanMbus8A 37 }

hmWanMbus8AVIF10		OBJECT-TYPE
			SYNTAX	INTEGER
			MAX-ACCESS	read-only
			STATUS	current
			::= { hmWanMbus8A 38 }

hmWanMbus8AValue10		OBJECT-TYPE
			SYNTAX	INTEGER
			MAX-ACCESS	read-only
			STATUS	current
			::= { hmWanMbus8A 39 }

hmWanMbus8AVIF11		OBJECT-TYPE
			SYNTAX	INTEGER
			MAX-ACCESS	read-only
			STATUS	current
			::= { hmWanMbus8A 40 }

hmWanMbus8AValue11		OBJECT-TYPE
			SYNTAX	INTEGER
			MAX-ACCESS	read-only
			STATUS	current
			::= { hmWanMbus8A 41 }

hmWanMbus8AVIF12		OBJECT-TYPE
			SYNTAX	INTEGER
			MAX-ACCESS	read-only
			STATUS	current
			::= { hmWanMbus8A 42 }

hmWanMbus8AValue12		OBJECT-TYPE
			SYNTAX	INTEGER
			MAX-ACCESS	read-only
			STATUS	current
			::= { hmWanMbus8A 43 }

hmWanMbus8AVIF13		OBJECT-TYPE
			SYNTAX	INTEGER
			MAX-ACCESS	read-only
			STATUS	current
			::= { hmWanMbus8A 44 }

hmWanMbus8AValue13		OBJECT-TYPE
			SYNTAX	INTEGER
			MAX-ACCESS	read-only
			STATUS	current
			::= { hmWanMbus8A 45 }

hmWanMbus8AVIF14		OBJECT-TYPE
			SYNTAX	INTEGER
			MAX-ACCESS	read-only
			STATUS	current
			::= { hmWanMbus8A 46 }

hmWanMbus8AValue14		OBJECT-TYPE
			SYNTAX	INTEGER
			MAX-ACCESS	read-only
			STATUS	current
			::= { hmWanMbus8A 47 }

hmWanMbus8AVIF15		OBJECT-TYPE
			SYNTAX	INTEGER
			MAX-ACCESS	read-only
			STATUS	current
			::= { hmWanMbus8A 48 }

hmWanMbus8AValue15		OBJECT-TYPE
			SYNTAX	INTEGER
			MAX-ACCESS	read-only
			STATUS	current
			::= { hmWanMbus8A 49 }

hmWanMbus8AVIF16		OBJECT-TYPE
			SYNTAX	INTEGER
			MAX-ACCESS	read-only
			STATUS	current
			::= { hmWanMbus8A 50 }

hmWanMbus8AValue16		OBJECT-TYPE
			SYNTAX	INTEGER
			MAX-ACCESS	read-only
			STATUS	current
			::= { hmWanMbus8A 51 }

hmWanMbus8AVIF17		OBJECT-TYPE
			SYNTAX	INTEGER
			MAX-ACCESS	read-only
			STATUS	current
			::= { hmWanMbus8A 52 }

hmWanMbus8AValue17		OBJECT-TYPE
			SYNTAX	INTEGER
			MAX-ACCESS	read-only
			STATUS	current
			::= { hmWanMbus8A 53 }

hmWanMbus8AVIF18		OBJECT-TYPE
			SYNTAX	INTEGER
			MAX-ACCESS	read-only
			STATUS	current
			::= { hmWanMbus8A 54 }

hmWanMbus8AValue18		OBJECT-TYPE
			SYNTAX	INTEGER
			MAX-ACCESS	read-only
			STATUS	current
			::= { hmWanMbus8A 55 }

hmWanMbus8AVIF19		OBJECT-TYPE
			SYNTAX	INTEGER
			MAX-ACCESS	read-only
			STATUS	current
			::= { hmWanMbus8A 56 }

hmWanMbus8AValue19		OBJECT-TYPE
			SYNTAX	INTEGER
			MAX-ACCESS	read-only
			STATUS	current
			::= { hmWanMbus8A 57 }

hmWanMbus8AVIF1A		OBJECT-TYPE
			SYNTAX	INTEGER
			MAX-ACCESS	read-only
			STATUS	current
			::= { hmWanMbus8A 58 }

hmWanMbus8AValue1A		OBJECT-TYPE
			SYNTAX	INTEGER
			MAX-ACCESS	read-only
			STATUS	current
			::= { hmWanMbus8A 59 }

hmWanMbus8AVIF1B		OBJECT-TYPE
			SYNTAX	INTEGER
			MAX-ACCESS	read-only
			STATUS	current
			::= { hmWanMbus8A 60 }

hmWanMbus8AValue1B		OBJECT-TYPE
			SYNTAX	INTEGER
			MAX-ACCESS	read-only
			STATUS	current
			::= { hmWanMbus8A 61 }

hmWanMbus8AVIF1C		OBJECT-TYPE
			SYNTAX	INTEGER
			MAX-ACCESS	read-only
			STATUS	current
			::= { hmWanMbus8A 62 }

hmWanMbus8AValue1C		OBJECT-TYPE
			SYNTAX	INTEGER
			MAX-ACCESS	read-only
			STATUS	current
			::= { hmWanMbus8A 63 }

hmWanMbus8AVIF1D		OBJECT-TYPE
			SYNTAX	INTEGER
			MAX-ACCESS	read-only
			STATUS	current
			::= { hmWanMbus8A 64 }

hmWanMbus8AValue1D		OBJECT-TYPE
			SYNTAX	INTEGER
			MAX-ACCESS	read-only
			STATUS	current
			::= { hmWanMbus8A 65 }

hmWanMbus8AVIF1E		OBJECT-TYPE
			SYNTAX	INTEGER
			MAX-ACCESS	read-only
			STATUS	current
			::= { hmWanMbus8A 66 }

hmWanMbus8AValue1E		OBJECT-TYPE
			SYNTAX	INTEGER
			MAX-ACCESS	read-only
			STATUS	current
			::= { hmWanMbus8A 67 }

hmWanMbus8AVIF1F		OBJECT-TYPE
			SYNTAX	INTEGER
			MAX-ACCESS	read-only
			STATUS	current
			::= { hmWanMbus8A 68 }

hmWanMbus8AValue1F		OBJECT-TYPE
			SYNTAX	INTEGER
			MAX-ACCESS	read-only
			STATUS	current
			::= { hmWanMbus8A 69 }

hmWanMbus8AVIF20		OBJECT-TYPE
			SYNTAX	INTEGER
			MAX-ACCESS	read-only
			STATUS	current
			::= { hmWanMbus8A 70 }

hmWanMbus8AValue20		OBJECT-TYPE
			SYNTAX	INTEGER
			MAX-ACCESS	read-only
			STATUS	current
			::= { hmWanMbus8A 71 }

hmWanMbus8AVIF21		OBJECT-TYPE
			SYNTAX	INTEGER
			MAX-ACCESS	read-only
			STATUS	current
			::= { hmWanMbus8A 72 }

hmWanMbus8AValue21		OBJECT-TYPE
			SYNTAX	INTEGER
			MAX-ACCESS	read-only
			STATUS	current
			::= { hmWanMbus8A 73 }

hmWanMbus8AVIF22		OBJECT-TYPE
			SYNTAX	INTEGER
			MAX-ACCESS	read-only
			STATUS	current
			::= { hmWanMbus8A 74 }

hmWanMbus8AValue22		OBJECT-TYPE
			SYNTAX	INTEGER
			MAX-ACCESS	read-only
			STATUS	current
			::= { hmWanMbus8A 75 }

hmWanMbus8AVIF23		OBJECT-TYPE
			SYNTAX	INTEGER
			MAX-ACCESS	read-only
			STATUS	current
			::= { hmWanMbus8A 76 }

hmWanMbus8AValue23		OBJECT-TYPE
			SYNTAX	INTEGER
			MAX-ACCESS	read-only
			STATUS	current
			::= { hmWanMbus8A 77 }

hmWanMbus8AVIF24		OBJECT-TYPE
			SYNTAX	INTEGER
			MAX-ACCESS	read-only
			STATUS	current
			::= { hmWanMbus8A 78 }

hmWanMbus8AValue24		OBJECT-TYPE
			SYNTAX	INTEGER
			MAX-ACCESS	read-only
			STATUS	current
			::= { hmWanMbus8A 79 }

hmWanMbus8AVIF25		OBJECT-TYPE
			SYNTAX	INTEGER
			MAX-ACCESS	read-only
			STATUS	current
			::= { hmWanMbus8A 80 }

hmWanMbus8AValue25		OBJECT-TYPE
			SYNTAX	INTEGER
			MAX-ACCESS	read-only
			STATUS	current
			::= { hmWanMbus8A 81 }

hmWanMbus8AVIF26		OBJECT-TYPE
			SYNTAX	INTEGER
			MAX-ACCESS	read-only
			STATUS	current
			::= { hmWanMbus8A 82 }

hmWanMbus8AValue26		OBJECT-TYPE
			SYNTAX	INTEGER
			MAX-ACCESS	read-only
			STATUS	current
			::= { hmWanMbus8A 83 }

hmWanMbus8AVIF27		OBJECT-TYPE
			SYNTAX	INTEGER
			MAX-ACCESS	read-only
			STATUS	current
			::= { hmWanMbus8A 84 }

hmWanMbus8AValue27		OBJECT-TYPE
			SYNTAX	INTEGER
			MAX-ACCESS	read-only
			STATUS	current
			::= { hmWanMbus8A 85 }

hmWanMbus8AVIF28		OBJECT-TYPE
			SYNTAX	INTEGER
			MAX-ACCESS	read-only
			STATUS	current
			::= { hmWanMbus8A 86 }

hmWanMbus8AValue28		OBJECT-TYPE
			SYNTAX	INTEGER
			MAX-ACCESS	read-only
			STATUS	current
			::= { hmWanMbus8A 87 }

hmWanMbus8AVIF29		OBJECT-TYPE
			SYNTAX	INTEGER
			MAX-ACCESS	read-only
			STATUS	current
			::= { hmWanMbus8A 88 }

hmWanMbus8AValue29		OBJECT-TYPE
			SYNTAX	INTEGER
			MAX-ACCESS	read-only
			STATUS	current
			::= { hmWanMbus8A 89 }

hmWanMbus8AVIF2A		OBJECT-TYPE
			SYNTAX	INTEGER
			MAX-ACCESS	read-only
			STATUS	current
			::= { hmWanMbus8A 90 }

hmWanMbus8AValue2A		OBJECT-TYPE
			SYNTAX	INTEGER
			MAX-ACCESS	read-only
			STATUS	current
			::= { hmWanMbus8A 91 }

hmWanMbus8AVIF2B		OBJECT-TYPE
			SYNTAX	INTEGER
			MAX-ACCESS	read-only
			STATUS	current
			::= { hmWanMbus8A 92 }

hmWanMbus8AValue2B		OBJECT-TYPE
			SYNTAX	INTEGER
			MAX-ACCESS	read-only
			STATUS	current
			::= { hmWanMbus8A 93 }

hmWanMbus8AVIF2C		OBJECT-TYPE
			SYNTAX	INTEGER
			MAX-ACCESS	read-only
			STATUS	current
			::= { hmWanMbus8A 94 }

hmWanMbus8AValue2C		OBJECT-TYPE
			SYNTAX	INTEGER
			MAX-ACCESS	read-only
			STATUS	current
			::= { hmWanMbus8A 95 }

hmWanMbus8AVIF2D		OBJECT-TYPE
			SYNTAX	INTEGER
			MAX-ACCESS	read-only
			STATUS	current
			::= { hmWanMbus8A 96 }

hmWanMbus8AValue2D		OBJECT-TYPE
			SYNTAX	INTEGER
			MAX-ACCESS	read-only
			STATUS	current
			::= { hmWanMbus8A 97 }

hmWanMbus8AVIF2E		OBJECT-TYPE
			SYNTAX	INTEGER
			MAX-ACCESS	read-only
			STATUS	current
			::= { hmWanMbus8A 98 }

hmWanMbus8AValue2E		OBJECT-TYPE
			SYNTAX	INTEGER
			MAX-ACCESS	read-only
			STATUS	current
			::= { hmWanMbus8A 99 }

hmWanMbus8AVIF2F		OBJECT-TYPE
			SYNTAX	INTEGER
			MAX-ACCESS	read-only
			STATUS	current
			::= { hmWanMbus8A 100 }

hmWanMbus8AValue2F		OBJECT-TYPE
			SYNTAX	INTEGER
			MAX-ACCESS	read-only
			STATUS	current
			::= { hmWanMbus8A 101 }

hmWanMbus8B			OBJECT IDENTIFIER ::= { hmWanMbus 139 }

hmWanMbus8BIdNumber		OBJECT-TYPE
			SYNTAX	Gauge32
			MAX-ACCESS	read-only
			STATUS	current
			::= { hmWanMbus8B 1 }

hmWanMbus8BManufacturer	OBJECT-TYPE
			SYNTAX	Gauge32
			MAX-ACCESS	read-only
			STATUS	current
			::= { hmWanMbus8B 2 }

hmWanMbus8BVersion		OBJECT-TYPE
			SYNTAX	Gauge32
			MAX-ACCESS	read-only
			STATUS	current
			::= { hmWanMbus8B 3 }

hmWanMbus8BMedium		OBJECT-TYPE
			SYNTAX	Gauge32
			MAX-ACCESS	read-only
			STATUS	current
			::= { hmWanMbus8B 4 }

hmWanMbus8BStatus		OBJECT-TYPE
			SYNTAX	Gauge32
			MAX-ACCESS	read-only
			STATUS	current
			::= { hmWanMbus8B 5 }

hmWanMbus8BVIF00		OBJECT-TYPE
			SYNTAX	INTEGER
			MAX-ACCESS	read-only
			STATUS	current
			::= { hmWanMbus8B 6 }

hmWanMbus8BValue00		OBJECT-TYPE
			SYNTAX	INTEGER
			MAX-ACCESS	read-only
			STATUS	current
			::= { hmWanMbus8B 7 }

hmWanMbus8BVIF01		OBJECT-TYPE
			SYNTAX	INTEGER
			MAX-ACCESS	read-only
			STATUS	current
			::= { hmWanMbus8B 8 }

hmWanMbus8BValue01		OBJECT-TYPE
			SYNTAX	INTEGER
			MAX-ACCESS	read-only
			STATUS	current
			::= { hmWanMbus8B 9 }

hmWanMbus8BVIF02		OBJECT-TYPE
			SYNTAX	INTEGER
			MAX-ACCESS	read-only
			STATUS	current
			::= { hmWanMbus8B 10 }

hmWanMbus8BValue02		OBJECT-TYPE
			SYNTAX	INTEGER
			MAX-ACCESS	read-only
			STATUS	current
			::= { hmWanMbus8B 11 }

hmWanMbus8BVIF03		OBJECT-TYPE
			SYNTAX	INTEGER
			MAX-ACCESS	read-only
			STATUS	current
			::= { hmWanMbus8B 12 }

hmWanMbus8BValue03		OBJECT-TYPE
			SYNTAX	INTEGER
			MAX-ACCESS	read-only
			STATUS	current
			::= { hmWanMbus8B 13 }

hmWanMbus8BVIF04		OBJECT-TYPE
			SYNTAX	INTEGER
			MAX-ACCESS	read-only
			STATUS	current
			::= { hmWanMbus8B 14 }

hmWanMbus8BValue04		OBJECT-TYPE
			SYNTAX	INTEGER
			MAX-ACCESS	read-only
			STATUS	current
			::= { hmWanMbus8B 15 }

hmWanMbus8BVIF05		OBJECT-TYPE
			SYNTAX	INTEGER
			MAX-ACCESS	read-only
			STATUS	current
			::= { hmWanMbus8B 16 }

hmWanMbus8BValue05		OBJECT-TYPE
			SYNTAX	INTEGER
			MAX-ACCESS	read-only
			STATUS	current
			::= { hmWanMbus8B 17 }

hmWanMbus8BVIF06		OBJECT-TYPE
			SYNTAX	INTEGER
			MAX-ACCESS	read-only
			STATUS	current
			::= { hmWanMbus8B 18 }

hmWanMbus8BValue06		OBJECT-TYPE
			SYNTAX	INTEGER
			MAX-ACCESS	read-only
			STATUS	current
			::= { hmWanMbus8B 19 }

hmWanMbus8BVIF07		OBJECT-TYPE
			SYNTAX	INTEGER
			MAX-ACCESS	read-only
			STATUS	current
			::= { hmWanMbus8B 20 }

hmWanMbus8BValue07		OBJECT-TYPE
			SYNTAX	INTEGER
			MAX-ACCESS	read-only
			STATUS	current
			::= { hmWanMbus8B 21 }

hmWanMbus8BVIF08		OBJECT-TYPE
			SYNTAX	INTEGER
			MAX-ACCESS	read-only
			STATUS	current
			::= { hmWanMbus8B 22 }

hmWanMbus8BValue08		OBJECT-TYPE
			SYNTAX	INTEGER
			MAX-ACCESS	read-only
			STATUS	current
			::= { hmWanMbus8B 23 }

hmWanMbus8BVIF09		OBJECT-TYPE
			SYNTAX	INTEGER
			MAX-ACCESS	read-only
			STATUS	current
			::= { hmWanMbus8B 24 }

hmWanMbus8BValue09		OBJECT-TYPE
			SYNTAX	INTEGER
			MAX-ACCESS	read-only
			STATUS	current
			::= { hmWanMbus8B 25 }

hmWanMbus8BVIF0A		OBJECT-TYPE
			SYNTAX	INTEGER
			MAX-ACCESS	read-only
			STATUS	current
			::= { hmWanMbus8B 26 }

hmWanMbus8BValue0A		OBJECT-TYPE
			SYNTAX	INTEGER
			MAX-ACCESS	read-only
			STATUS	current
			::= { hmWanMbus8B 27 }

hmWanMbus8BVIF0B		OBJECT-TYPE
			SYNTAX	INTEGER
			MAX-ACCESS	read-only
			STATUS	current
			::= { hmWanMbus8B 28 }

hmWanMbus8BValue0B		OBJECT-TYPE
			SYNTAX	INTEGER
			MAX-ACCESS	read-only
			STATUS	current
			::= { hmWanMbus8B 29 }

hmWanMbus8BVIF0C		OBJECT-TYPE
			SYNTAX	INTEGER
			MAX-ACCESS	read-only
			STATUS	current
			::= { hmWanMbus8B 30 }

hmWanMbus8BValue0C		OBJECT-TYPE
			SYNTAX	INTEGER
			MAX-ACCESS	read-only
			STATUS	current
			::= { hmWanMbus8B 31 }

hmWanMbus8BVIF0D		OBJECT-TYPE
			SYNTAX	INTEGER
			MAX-ACCESS	read-only
			STATUS	current
			::= { hmWanMbus8B 32 }

hmWanMbus8BValue0D		OBJECT-TYPE
			SYNTAX	INTEGER
			MAX-ACCESS	read-only
			STATUS	current
			::= { hmWanMbus8B 33 }

hmWanMbus8BVIF0E		OBJECT-TYPE
			SYNTAX	INTEGER
			MAX-ACCESS	read-only
			STATUS	current
			::= { hmWanMbus8B 34 }

hmWanMbus8BValue0E		OBJECT-TYPE
			SYNTAX	INTEGER
			MAX-ACCESS	read-only
			STATUS	current
			::= { hmWanMbus8B 35 }

hmWanMbus8BVIF0F		OBJECT-TYPE
			SYNTAX	INTEGER
			MAX-ACCESS	read-only
			STATUS	current
			::= { hmWanMbus8B 36 }

hmWanMbus8BValue0F		OBJECT-TYPE
			SYNTAX	INTEGER
			MAX-ACCESS	read-only
			STATUS	current
			::= { hmWanMbus8B 37 }

hmWanMbus8BVIF10		OBJECT-TYPE
			SYNTAX	INTEGER
			MAX-ACCESS	read-only
			STATUS	current
			::= { hmWanMbus8B 38 }

hmWanMbus8BValue10		OBJECT-TYPE
			SYNTAX	INTEGER
			MAX-ACCESS	read-only
			STATUS	current
			::= { hmWanMbus8B 39 }

hmWanMbus8BVIF11		OBJECT-TYPE
			SYNTAX	INTEGER
			MAX-ACCESS	read-only
			STATUS	current
			::= { hmWanMbus8B 40 }

hmWanMbus8BValue11		OBJECT-TYPE
			SYNTAX	INTEGER
			MAX-ACCESS	read-only
			STATUS	current
			::= { hmWanMbus8B 41 }

hmWanMbus8BVIF12		OBJECT-TYPE
			SYNTAX	INTEGER
			MAX-ACCESS	read-only
			STATUS	current
			::= { hmWanMbus8B 42 }

hmWanMbus8BValue12		OBJECT-TYPE
			SYNTAX	INTEGER
			MAX-ACCESS	read-only
			STATUS	current
			::= { hmWanMbus8B 43 }

hmWanMbus8BVIF13		OBJECT-TYPE
			SYNTAX	INTEGER
			MAX-ACCESS	read-only
			STATUS	current
			::= { hmWanMbus8B 44 }

hmWanMbus8BValue13		OBJECT-TYPE
			SYNTAX	INTEGER
			MAX-ACCESS	read-only
			STATUS	current
			::= { hmWanMbus8B 45 }

hmWanMbus8BVIF14		OBJECT-TYPE
			SYNTAX	INTEGER
			MAX-ACCESS	read-only
			STATUS	current
			::= { hmWanMbus8B 46 }

hmWanMbus8BValue14		OBJECT-TYPE
			SYNTAX	INTEGER
			MAX-ACCESS	read-only
			STATUS	current
			::= { hmWanMbus8B 47 }

hmWanMbus8BVIF15		OBJECT-TYPE
			SYNTAX	INTEGER
			MAX-ACCESS	read-only
			STATUS	current
			::= { hmWanMbus8B 48 }

hmWanMbus8BValue15		OBJECT-TYPE
			SYNTAX	INTEGER
			MAX-ACCESS	read-only
			STATUS	current
			::= { hmWanMbus8B 49 }

hmWanMbus8BVIF16		OBJECT-TYPE
			SYNTAX	INTEGER
			MAX-ACCESS	read-only
			STATUS	current
			::= { hmWanMbus8B 50 }

hmWanMbus8BValue16		OBJECT-TYPE
			SYNTAX	INTEGER
			MAX-ACCESS	read-only
			STATUS	current
			::= { hmWanMbus8B 51 }

hmWanMbus8BVIF17		OBJECT-TYPE
			SYNTAX	INTEGER
			MAX-ACCESS	read-only
			STATUS	current
			::= { hmWanMbus8B 52 }

hmWanMbus8BValue17		OBJECT-TYPE
			SYNTAX	INTEGER
			MAX-ACCESS	read-only
			STATUS	current
			::= { hmWanMbus8B 53 }

hmWanMbus8BVIF18		OBJECT-TYPE
			SYNTAX	INTEGER
			MAX-ACCESS	read-only
			STATUS	current
			::= { hmWanMbus8B 54 }

hmWanMbus8BValue18		OBJECT-TYPE
			SYNTAX	INTEGER
			MAX-ACCESS	read-only
			STATUS	current
			::= { hmWanMbus8B 55 }

hmWanMbus8BVIF19		OBJECT-TYPE
			SYNTAX	INTEGER
			MAX-ACCESS	read-only
			STATUS	current
			::= { hmWanMbus8B 56 }

hmWanMbus8BValue19		OBJECT-TYPE
			SYNTAX	INTEGER
			MAX-ACCESS	read-only
			STATUS	current
			::= { hmWanMbus8B 57 }

hmWanMbus8BVIF1A		OBJECT-TYPE
			SYNTAX	INTEGER
			MAX-ACCESS	read-only
			STATUS	current
			::= { hmWanMbus8B 58 }

hmWanMbus8BValue1A		OBJECT-TYPE
			SYNTAX	INTEGER
			MAX-ACCESS	read-only
			STATUS	current
			::= { hmWanMbus8B 59 }

hmWanMbus8BVIF1B		OBJECT-TYPE
			SYNTAX	INTEGER
			MAX-ACCESS	read-only
			STATUS	current
			::= { hmWanMbus8B 60 }

hmWanMbus8BValue1B		OBJECT-TYPE
			SYNTAX	INTEGER
			MAX-ACCESS	read-only
			STATUS	current
			::= { hmWanMbus8B 61 }

hmWanMbus8BVIF1C		OBJECT-TYPE
			SYNTAX	INTEGER
			MAX-ACCESS	read-only
			STATUS	current
			::= { hmWanMbus8B 62 }

hmWanMbus8BValue1C		OBJECT-TYPE
			SYNTAX	INTEGER
			MAX-ACCESS	read-only
			STATUS	current
			::= { hmWanMbus8B 63 }

hmWanMbus8BVIF1D		OBJECT-TYPE
			SYNTAX	INTEGER
			MAX-ACCESS	read-only
			STATUS	current
			::= { hmWanMbus8B 64 }

hmWanMbus8BValue1D		OBJECT-TYPE
			SYNTAX	INTEGER
			MAX-ACCESS	read-only
			STATUS	current
			::= { hmWanMbus8B 65 }

hmWanMbus8BVIF1E		OBJECT-TYPE
			SYNTAX	INTEGER
			MAX-ACCESS	read-only
			STATUS	current
			::= { hmWanMbus8B 66 }

hmWanMbus8BValue1E		OBJECT-TYPE
			SYNTAX	INTEGER
			MAX-ACCESS	read-only
			STATUS	current
			::= { hmWanMbus8B 67 }

hmWanMbus8BVIF1F		OBJECT-TYPE
			SYNTAX	INTEGER
			MAX-ACCESS	read-only
			STATUS	current
			::= { hmWanMbus8B 68 }

hmWanMbus8BValue1F		OBJECT-TYPE
			SYNTAX	INTEGER
			MAX-ACCESS	read-only
			STATUS	current
			::= { hmWanMbus8B 69 }

hmWanMbus8BVIF20		OBJECT-TYPE
			SYNTAX	INTEGER
			MAX-ACCESS	read-only
			STATUS	current
			::= { hmWanMbus8B 70 }

hmWanMbus8BValue20		OBJECT-TYPE
			SYNTAX	INTEGER
			MAX-ACCESS	read-only
			STATUS	current
			::= { hmWanMbus8B 71 }

hmWanMbus8BVIF21		OBJECT-TYPE
			SYNTAX	INTEGER
			MAX-ACCESS	read-only
			STATUS	current
			::= { hmWanMbus8B 72 }

hmWanMbus8BValue21		OBJECT-TYPE
			SYNTAX	INTEGER
			MAX-ACCESS	read-only
			STATUS	current
			::= { hmWanMbus8B 73 }

hmWanMbus8BVIF22		OBJECT-TYPE
			SYNTAX	INTEGER
			MAX-ACCESS	read-only
			STATUS	current
			::= { hmWanMbus8B 74 }

hmWanMbus8BValue22		OBJECT-TYPE
			SYNTAX	INTEGER
			MAX-ACCESS	read-only
			STATUS	current
			::= { hmWanMbus8B 75 }

hmWanMbus8BVIF23		OBJECT-TYPE
			SYNTAX	INTEGER
			MAX-ACCESS	read-only
			STATUS	current
			::= { hmWanMbus8B 76 }

hmWanMbus8BValue23		OBJECT-TYPE
			SYNTAX	INTEGER
			MAX-ACCESS	read-only
			STATUS	current
			::= { hmWanMbus8B 77 }

hmWanMbus8BVIF24		OBJECT-TYPE
			SYNTAX	INTEGER
			MAX-ACCESS	read-only
			STATUS	current
			::= { hmWanMbus8B 78 }

hmWanMbus8BValue24		OBJECT-TYPE
			SYNTAX	INTEGER
			MAX-ACCESS	read-only
			STATUS	current
			::= { hmWanMbus8B 79 }

hmWanMbus8BVIF25		OBJECT-TYPE
			SYNTAX	INTEGER
			MAX-ACCESS	read-only
			STATUS	current
			::= { hmWanMbus8B 80 }

hmWanMbus8BValue25		OBJECT-TYPE
			SYNTAX	INTEGER
			MAX-ACCESS	read-only
			STATUS	current
			::= { hmWanMbus8B 81 }

hmWanMbus8BVIF26		OBJECT-TYPE
			SYNTAX	INTEGER
			MAX-ACCESS	read-only
			STATUS	current
			::= { hmWanMbus8B 82 }

hmWanMbus8BValue26		OBJECT-TYPE
			SYNTAX	INTEGER
			MAX-ACCESS	read-only
			STATUS	current
			::= { hmWanMbus8B 83 }

hmWanMbus8BVIF27		OBJECT-TYPE
			SYNTAX	INTEGER
			MAX-ACCESS	read-only
			STATUS	current
			::= { hmWanMbus8B 84 }

hmWanMbus8BValue27		OBJECT-TYPE
			SYNTAX	INTEGER
			MAX-ACCESS	read-only
			STATUS	current
			::= { hmWanMbus8B 85 }

hmWanMbus8BVIF28		OBJECT-TYPE
			SYNTAX	INTEGER
			MAX-ACCESS	read-only
			STATUS	current
			::= { hmWanMbus8B 86 }

hmWanMbus8BValue28		OBJECT-TYPE
			SYNTAX	INTEGER
			MAX-ACCESS	read-only
			STATUS	current
			::= { hmWanMbus8B 87 }

hmWanMbus8BVIF29		OBJECT-TYPE
			SYNTAX	INTEGER
			MAX-ACCESS	read-only
			STATUS	current
			::= { hmWanMbus8B 88 }

hmWanMbus8BValue29		OBJECT-TYPE
			SYNTAX	INTEGER
			MAX-ACCESS	read-only
			STATUS	current
			::= { hmWanMbus8B 89 }

hmWanMbus8BVIF2A		OBJECT-TYPE
			SYNTAX	INTEGER
			MAX-ACCESS	read-only
			STATUS	current
			::= { hmWanMbus8B 90 }

hmWanMbus8BValue2A		OBJECT-TYPE
			SYNTAX	INTEGER
			MAX-ACCESS	read-only
			STATUS	current
			::= { hmWanMbus8B 91 }

hmWanMbus8BVIF2B		OBJECT-TYPE
			SYNTAX	INTEGER
			MAX-ACCESS	read-only
			STATUS	current
			::= { hmWanMbus8B 92 }

hmWanMbus8BValue2B		OBJECT-TYPE
			SYNTAX	INTEGER
			MAX-ACCESS	read-only
			STATUS	current
			::= { hmWanMbus8B 93 }

hmWanMbus8BVIF2C		OBJECT-TYPE
			SYNTAX	INTEGER
			MAX-ACCESS	read-only
			STATUS	current
			::= { hmWanMbus8B 94 }

hmWanMbus8BValue2C		OBJECT-TYPE
			SYNTAX	INTEGER
			MAX-ACCESS	read-only
			STATUS	current
			::= { hmWanMbus8B 95 }

hmWanMbus8BVIF2D		OBJECT-TYPE
			SYNTAX	INTEGER
			MAX-ACCESS	read-only
			STATUS	current
			::= { hmWanMbus8B 96 }

hmWanMbus8BValue2D		OBJECT-TYPE
			SYNTAX	INTEGER
			MAX-ACCESS	read-only
			STATUS	current
			::= { hmWanMbus8B 97 }

hmWanMbus8BVIF2E		OBJECT-TYPE
			SYNTAX	INTEGER
			MAX-ACCESS	read-only
			STATUS	current
			::= { hmWanMbus8B 98 }

hmWanMbus8BValue2E		OBJECT-TYPE
			SYNTAX	INTEGER
			MAX-ACCESS	read-only
			STATUS	current
			::= { hmWanMbus8B 99 }

hmWanMbus8BVIF2F		OBJECT-TYPE
			SYNTAX	INTEGER
			MAX-ACCESS	read-only
			STATUS	current
			::= { hmWanMbus8B 100 }

hmWanMbus8BValue2F		OBJECT-TYPE
			SYNTAX	INTEGER
			MAX-ACCESS	read-only
			STATUS	current
			::= { hmWanMbus8B 101 }

hmWanMbus8C			OBJECT IDENTIFIER ::= { hmWanMbus 140 }

hmWanMbus8CIdNumber		OBJECT-TYPE
			SYNTAX	Gauge32
			MAX-ACCESS	read-only
			STATUS	current
			::= { hmWanMbus8C 1 }

hmWanMbus8CManufacturer	OBJECT-TYPE
			SYNTAX	Gauge32
			MAX-ACCESS	read-only
			STATUS	current
			::= { hmWanMbus8C 2 }

hmWanMbus8CVersion		OBJECT-TYPE
			SYNTAX	Gauge32
			MAX-ACCESS	read-only
			STATUS	current
			::= { hmWanMbus8C 3 }

hmWanMbus8CMedium		OBJECT-TYPE
			SYNTAX	Gauge32
			MAX-ACCESS	read-only
			STATUS	current
			::= { hmWanMbus8C 4 }

hmWanMbus8CStatus		OBJECT-TYPE
			SYNTAX	Gauge32
			MAX-ACCESS	read-only
			STATUS	current
			::= { hmWanMbus8C 5 }

hmWanMbus8CVIF00		OBJECT-TYPE
			SYNTAX	INTEGER
			MAX-ACCESS	read-only
			STATUS	current
			::= { hmWanMbus8C 6 }

hmWanMbus8CValue00		OBJECT-TYPE
			SYNTAX	INTEGER
			MAX-ACCESS	read-only
			STATUS	current
			::= { hmWanMbus8C 7 }

hmWanMbus8CVIF01		OBJECT-TYPE
			SYNTAX	INTEGER
			MAX-ACCESS	read-only
			STATUS	current
			::= { hmWanMbus8C 8 }

hmWanMbus8CValue01		OBJECT-TYPE
			SYNTAX	INTEGER
			MAX-ACCESS	read-only
			STATUS	current
			::= { hmWanMbus8C 9 }

hmWanMbus8CVIF02		OBJECT-TYPE
			SYNTAX	INTEGER
			MAX-ACCESS	read-only
			STATUS	current
			::= { hmWanMbus8C 10 }

hmWanMbus8CValue02		OBJECT-TYPE
			SYNTAX	INTEGER
			MAX-ACCESS	read-only
			STATUS	current
			::= { hmWanMbus8C 11 }

hmWanMbus8CVIF03		OBJECT-TYPE
			SYNTAX	INTEGER
			MAX-ACCESS	read-only
			STATUS	current
			::= { hmWanMbus8C 12 }

hmWanMbus8CValue03		OBJECT-TYPE
			SYNTAX	INTEGER
			MAX-ACCESS	read-only
			STATUS	current
			::= { hmWanMbus8C 13 }

hmWanMbus8CVIF04		OBJECT-TYPE
			SYNTAX	INTEGER
			MAX-ACCESS	read-only
			STATUS	current
			::= { hmWanMbus8C 14 }

hmWanMbus8CValue04		OBJECT-TYPE
			SYNTAX	INTEGER
			MAX-ACCESS	read-only
			STATUS	current
			::= { hmWanMbus8C 15 }

hmWanMbus8CVIF05		OBJECT-TYPE
			SYNTAX	INTEGER
			MAX-ACCESS	read-only
			STATUS	current
			::= { hmWanMbus8C 16 }

hmWanMbus8CValue05		OBJECT-TYPE
			SYNTAX	INTEGER
			MAX-ACCESS	read-only
			STATUS	current
			::= { hmWanMbus8C 17 }

hmWanMbus8CVIF06		OBJECT-TYPE
			SYNTAX	INTEGER
			MAX-ACCESS	read-only
			STATUS	current
			::= { hmWanMbus8C 18 }

hmWanMbus8CValue06		OBJECT-TYPE
			SYNTAX	INTEGER
			MAX-ACCESS	read-only
			STATUS	current
			::= { hmWanMbus8C 19 }

hmWanMbus8CVIF07		OBJECT-TYPE
			SYNTAX	INTEGER
			MAX-ACCESS	read-only
			STATUS	current
			::= { hmWanMbus8C 20 }

hmWanMbus8CValue07		OBJECT-TYPE
			SYNTAX	INTEGER
			MAX-ACCESS	read-only
			STATUS	current
			::= { hmWanMbus8C 21 }

hmWanMbus8CVIF08		OBJECT-TYPE
			SYNTAX	INTEGER
			MAX-ACCESS	read-only
			STATUS	current
			::= { hmWanMbus8C 22 }

hmWanMbus8CValue08		OBJECT-TYPE
			SYNTAX	INTEGER
			MAX-ACCESS	read-only
			STATUS	current
			::= { hmWanMbus8C 23 }

hmWanMbus8CVIF09		OBJECT-TYPE
			SYNTAX	INTEGER
			MAX-ACCESS	read-only
			STATUS	current
			::= { hmWanMbus8C 24 }

hmWanMbus8CValue09		OBJECT-TYPE
			SYNTAX	INTEGER
			MAX-ACCESS	read-only
			STATUS	current
			::= { hmWanMbus8C 25 }

hmWanMbus8CVIF0A		OBJECT-TYPE
			SYNTAX	INTEGER
			MAX-ACCESS	read-only
			STATUS	current
			::= { hmWanMbus8C 26 }

hmWanMbus8CValue0A		OBJECT-TYPE
			SYNTAX	INTEGER
			MAX-ACCESS	read-only
			STATUS	current
			::= { hmWanMbus8C 27 }

hmWanMbus8CVIF0B		OBJECT-TYPE
			SYNTAX	INTEGER
			MAX-ACCESS	read-only
			STATUS	current
			::= { hmWanMbus8C 28 }

hmWanMbus8CValue0B		OBJECT-TYPE
			SYNTAX	INTEGER
			MAX-ACCESS	read-only
			STATUS	current
			::= { hmWanMbus8C 29 }

hmWanMbus8CVIF0C		OBJECT-TYPE
			SYNTAX	INTEGER
			MAX-ACCESS	read-only
			STATUS	current
			::= { hmWanMbus8C 30 }

hmWanMbus8CValue0C		OBJECT-TYPE
			SYNTAX	INTEGER
			MAX-ACCESS	read-only
			STATUS	current
			::= { hmWanMbus8C 31 }

hmWanMbus8CVIF0D		OBJECT-TYPE
			SYNTAX	INTEGER
			MAX-ACCESS	read-only
			STATUS	current
			::= { hmWanMbus8C 32 }

hmWanMbus8CValue0D		OBJECT-TYPE
			SYNTAX	INTEGER
			MAX-ACCESS	read-only
			STATUS	current
			::= { hmWanMbus8C 33 }

hmWanMbus8CVIF0E		OBJECT-TYPE
			SYNTAX	INTEGER
			MAX-ACCESS	read-only
			STATUS	current
			::= { hmWanMbus8C 34 }

hmWanMbus8CValue0E		OBJECT-TYPE
			SYNTAX	INTEGER
			MAX-ACCESS	read-only
			STATUS	current
			::= { hmWanMbus8C 35 }

hmWanMbus8CVIF0F		OBJECT-TYPE
			SYNTAX	INTEGER
			MAX-ACCESS	read-only
			STATUS	current
			::= { hmWanMbus8C 36 }

hmWanMbus8CValue0F		OBJECT-TYPE
			SYNTAX	INTEGER
			MAX-ACCESS	read-only
			STATUS	current
			::= { hmWanMbus8C 37 }

hmWanMbus8CVIF10		OBJECT-TYPE
			SYNTAX	INTEGER
			MAX-ACCESS	read-only
			STATUS	current
			::= { hmWanMbus8C 38 }

hmWanMbus8CValue10		OBJECT-TYPE
			SYNTAX	INTEGER
			MAX-ACCESS	read-only
			STATUS	current
			::= { hmWanMbus8C 39 }

hmWanMbus8CVIF11		OBJECT-TYPE
			SYNTAX	INTEGER
			MAX-ACCESS	read-only
			STATUS	current
			::= { hmWanMbus8C 40 }

hmWanMbus8CValue11		OBJECT-TYPE
			SYNTAX	INTEGER
			MAX-ACCESS	read-only
			STATUS	current
			::= { hmWanMbus8C 41 }

hmWanMbus8CVIF12		OBJECT-TYPE
			SYNTAX	INTEGER
			MAX-ACCESS	read-only
			STATUS	current
			::= { hmWanMbus8C 42 }

hmWanMbus8CValue12		OBJECT-TYPE
			SYNTAX	INTEGER
			MAX-ACCESS	read-only
			STATUS	current
			::= { hmWanMbus8C 43 }

hmWanMbus8CVIF13		OBJECT-TYPE
			SYNTAX	INTEGER
			MAX-ACCESS	read-only
			STATUS	current
			::= { hmWanMbus8C 44 }

hmWanMbus8CValue13		OBJECT-TYPE
			SYNTAX	INTEGER
			MAX-ACCESS	read-only
			STATUS	current
			::= { hmWanMbus8C 45 }

hmWanMbus8CVIF14		OBJECT-TYPE
			SYNTAX	INTEGER
			MAX-ACCESS	read-only
			STATUS	current
			::= { hmWanMbus8C 46 }

hmWanMbus8CValue14		OBJECT-TYPE
			SYNTAX	INTEGER
			MAX-ACCESS	read-only
			STATUS	current
			::= { hmWanMbus8C 47 }

hmWanMbus8CVIF15		OBJECT-TYPE
			SYNTAX	INTEGER
			MAX-ACCESS	read-only
			STATUS	current
			::= { hmWanMbus8C 48 }

hmWanMbus8CValue15		OBJECT-TYPE
			SYNTAX	INTEGER
			MAX-ACCESS	read-only
			STATUS	current
			::= { hmWanMbus8C 49 }

hmWanMbus8CVIF16		OBJECT-TYPE
			SYNTAX	INTEGER
			MAX-ACCESS	read-only
			STATUS	current
			::= { hmWanMbus8C 50 }

hmWanMbus8CValue16		OBJECT-TYPE
			SYNTAX	INTEGER
			MAX-ACCESS	read-only
			STATUS	current
			::= { hmWanMbus8C 51 }

hmWanMbus8CVIF17		OBJECT-TYPE
			SYNTAX	INTEGER
			MAX-ACCESS	read-only
			STATUS	current
			::= { hmWanMbus8C 52 }

hmWanMbus8CValue17		OBJECT-TYPE
			SYNTAX	INTEGER
			MAX-ACCESS	read-only
			STATUS	current
			::= { hmWanMbus8C 53 }

hmWanMbus8CVIF18		OBJECT-TYPE
			SYNTAX	INTEGER
			MAX-ACCESS	read-only
			STATUS	current
			::= { hmWanMbus8C 54 }

hmWanMbus8CValue18		OBJECT-TYPE
			SYNTAX	INTEGER
			MAX-ACCESS	read-only
			STATUS	current
			::= { hmWanMbus8C 55 }

hmWanMbus8CVIF19		OBJECT-TYPE
			SYNTAX	INTEGER
			MAX-ACCESS	read-only
			STATUS	current
			::= { hmWanMbus8C 56 }

hmWanMbus8CValue19		OBJECT-TYPE
			SYNTAX	INTEGER
			MAX-ACCESS	read-only
			STATUS	current
			::= { hmWanMbus8C 57 }

hmWanMbus8CVIF1A		OBJECT-TYPE
			SYNTAX	INTEGER
			MAX-ACCESS	read-only
			STATUS	current
			::= { hmWanMbus8C 58 }

hmWanMbus8CValue1A		OBJECT-TYPE
			SYNTAX	INTEGER
			MAX-ACCESS	read-only
			STATUS	current
			::= { hmWanMbus8C 59 }

hmWanMbus8CVIF1B		OBJECT-TYPE
			SYNTAX	INTEGER
			MAX-ACCESS	read-only
			STATUS	current
			::= { hmWanMbus8C 60 }

hmWanMbus8CValue1B		OBJECT-TYPE
			SYNTAX	INTEGER
			MAX-ACCESS	read-only
			STATUS	current
			::= { hmWanMbus8C 61 }

hmWanMbus8CVIF1C		OBJECT-TYPE
			SYNTAX	INTEGER
			MAX-ACCESS	read-only
			STATUS	current
			::= { hmWanMbus8C 62 }

hmWanMbus8CValue1C		OBJECT-TYPE
			SYNTAX	INTEGER
			MAX-ACCESS	read-only
			STATUS	current
			::= { hmWanMbus8C 63 }

hmWanMbus8CVIF1D		OBJECT-TYPE
			SYNTAX	INTEGER
			MAX-ACCESS	read-only
			STATUS	current
			::= { hmWanMbus8C 64 }

hmWanMbus8CValue1D		OBJECT-TYPE
			SYNTAX	INTEGER
			MAX-ACCESS	read-only
			STATUS	current
			::= { hmWanMbus8C 65 }

hmWanMbus8CVIF1E		OBJECT-TYPE
			SYNTAX	INTEGER
			MAX-ACCESS	read-only
			STATUS	current
			::= { hmWanMbus8C 66 }

hmWanMbus8CValue1E		OBJECT-TYPE
			SYNTAX	INTEGER
			MAX-ACCESS	read-only
			STATUS	current
			::= { hmWanMbus8C 67 }

hmWanMbus8CVIF1F		OBJECT-TYPE
			SYNTAX	INTEGER
			MAX-ACCESS	read-only
			STATUS	current
			::= { hmWanMbus8C 68 }

hmWanMbus8CValue1F		OBJECT-TYPE
			SYNTAX	INTEGER
			MAX-ACCESS	read-only
			STATUS	current
			::= { hmWanMbus8C 69 }

hmWanMbus8CVIF20		OBJECT-TYPE
			SYNTAX	INTEGER
			MAX-ACCESS	read-only
			STATUS	current
			::= { hmWanMbus8C 70 }

hmWanMbus8CValue20		OBJECT-TYPE
			SYNTAX	INTEGER
			MAX-ACCESS	read-only
			STATUS	current
			::= { hmWanMbus8C 71 }

hmWanMbus8CVIF21		OBJECT-TYPE
			SYNTAX	INTEGER
			MAX-ACCESS	read-only
			STATUS	current
			::= { hmWanMbus8C 72 }

hmWanMbus8CValue21		OBJECT-TYPE
			SYNTAX	INTEGER
			MAX-ACCESS	read-only
			STATUS	current
			::= { hmWanMbus8C 73 }

hmWanMbus8CVIF22		OBJECT-TYPE
			SYNTAX	INTEGER
			MAX-ACCESS	read-only
			STATUS	current
			::= { hmWanMbus8C 74 }

hmWanMbus8CValue22		OBJECT-TYPE
			SYNTAX	INTEGER
			MAX-ACCESS	read-only
			STATUS	current
			::= { hmWanMbus8C 75 }

hmWanMbus8CVIF23		OBJECT-TYPE
			SYNTAX	INTEGER
			MAX-ACCESS	read-only
			STATUS	current
			::= { hmWanMbus8C 76 }

hmWanMbus8CValue23		OBJECT-TYPE
			SYNTAX	INTEGER
			MAX-ACCESS	read-only
			STATUS	current
			::= { hmWanMbus8C 77 }

hmWanMbus8CVIF24		OBJECT-TYPE
			SYNTAX	INTEGER
			MAX-ACCESS	read-only
			STATUS	current
			::= { hmWanMbus8C 78 }

hmWanMbus8CValue24		OBJECT-TYPE
			SYNTAX	INTEGER
			MAX-ACCESS	read-only
			STATUS	current
			::= { hmWanMbus8C 79 }

hmWanMbus8CVIF25		OBJECT-TYPE
			SYNTAX	INTEGER
			MAX-ACCESS	read-only
			STATUS	current
			::= { hmWanMbus8C 80 }

hmWanMbus8CValue25		OBJECT-TYPE
			SYNTAX	INTEGER
			MAX-ACCESS	read-only
			STATUS	current
			::= { hmWanMbus8C 81 }

hmWanMbus8CVIF26		OBJECT-TYPE
			SYNTAX	INTEGER
			MAX-ACCESS	read-only
			STATUS	current
			::= { hmWanMbus8C 82 }

hmWanMbus8CValue26		OBJECT-TYPE
			SYNTAX	INTEGER
			MAX-ACCESS	read-only
			STATUS	current
			::= { hmWanMbus8C 83 }

hmWanMbus8CVIF27		OBJECT-TYPE
			SYNTAX	INTEGER
			MAX-ACCESS	read-only
			STATUS	current
			::= { hmWanMbus8C 84 }

hmWanMbus8CValue27		OBJECT-TYPE
			SYNTAX	INTEGER
			MAX-ACCESS	read-only
			STATUS	current
			::= { hmWanMbus8C 85 }

hmWanMbus8CVIF28		OBJECT-TYPE
			SYNTAX	INTEGER
			MAX-ACCESS	read-only
			STATUS	current
			::= { hmWanMbus8C 86 }

hmWanMbus8CValue28		OBJECT-TYPE
			SYNTAX	INTEGER
			MAX-ACCESS	read-only
			STATUS	current
			::= { hmWanMbus8C 87 }

hmWanMbus8CVIF29		OBJECT-TYPE
			SYNTAX	INTEGER
			MAX-ACCESS	read-only
			STATUS	current
			::= { hmWanMbus8C 88 }

hmWanMbus8CValue29		OBJECT-TYPE
			SYNTAX	INTEGER
			MAX-ACCESS	read-only
			STATUS	current
			::= { hmWanMbus8C 89 }

hmWanMbus8CVIF2A		OBJECT-TYPE
			SYNTAX	INTEGER
			MAX-ACCESS	read-only
			STATUS	current
			::= { hmWanMbus8C 90 }

hmWanMbus8CValue2A		OBJECT-TYPE
			SYNTAX	INTEGER
			MAX-ACCESS	read-only
			STATUS	current
			::= { hmWanMbus8C 91 }

hmWanMbus8CVIF2B		OBJECT-TYPE
			SYNTAX	INTEGER
			MAX-ACCESS	read-only
			STATUS	current
			::= { hmWanMbus8C 92 }

hmWanMbus8CValue2B		OBJECT-TYPE
			SYNTAX	INTEGER
			MAX-ACCESS	read-only
			STATUS	current
			::= { hmWanMbus8C 93 }

hmWanMbus8CVIF2C		OBJECT-TYPE
			SYNTAX	INTEGER
			MAX-ACCESS	read-only
			STATUS	current
			::= { hmWanMbus8C 94 }

hmWanMbus8CValue2C		OBJECT-TYPE
			SYNTAX	INTEGER
			MAX-ACCESS	read-only
			STATUS	current
			::= { hmWanMbus8C 95 }

hmWanMbus8CVIF2D		OBJECT-TYPE
			SYNTAX	INTEGER
			MAX-ACCESS	read-only
			STATUS	current
			::= { hmWanMbus8C 96 }

hmWanMbus8CValue2D		OBJECT-TYPE
			SYNTAX	INTEGER
			MAX-ACCESS	read-only
			STATUS	current
			::= { hmWanMbus8C 97 }

hmWanMbus8CVIF2E		OBJECT-TYPE
			SYNTAX	INTEGER
			MAX-ACCESS	read-only
			STATUS	current
			::= { hmWanMbus8C 98 }

hmWanMbus8CValue2E		OBJECT-TYPE
			SYNTAX	INTEGER
			MAX-ACCESS	read-only
			STATUS	current
			::= { hmWanMbus8C 99 }

hmWanMbus8CVIF2F		OBJECT-TYPE
			SYNTAX	INTEGER
			MAX-ACCESS	read-only
			STATUS	current
			::= { hmWanMbus8C 100 }

hmWanMbus8CValue2F		OBJECT-TYPE
			SYNTAX	INTEGER
			MAX-ACCESS	read-only
			STATUS	current
			::= { hmWanMbus8C 101 }

hmWanMbus8D			OBJECT IDENTIFIER ::= { hmWanMbus 141 }

hmWanMbus8DIdNumber		OBJECT-TYPE
			SYNTAX	Gauge32
			MAX-ACCESS	read-only
			STATUS	current
			::= { hmWanMbus8D 1 }

hmWanMbus8DManufacturer	OBJECT-TYPE
			SYNTAX	Gauge32
			MAX-ACCESS	read-only
			STATUS	current
			::= { hmWanMbus8D 2 }

hmWanMbus8DVersion		OBJECT-TYPE
			SYNTAX	Gauge32
			MAX-ACCESS	read-only
			STATUS	current
			::= { hmWanMbus8D 3 }

hmWanMbus8DMedium		OBJECT-TYPE
			SYNTAX	Gauge32
			MAX-ACCESS	read-only
			STATUS	current
			::= { hmWanMbus8D 4 }

hmWanMbus8DStatus		OBJECT-TYPE
			SYNTAX	Gauge32
			MAX-ACCESS	read-only
			STATUS	current
			::= { hmWanMbus8D 5 }

hmWanMbus8DVIF00		OBJECT-TYPE
			SYNTAX	INTEGER
			MAX-ACCESS	read-only
			STATUS	current
			::= { hmWanMbus8D 6 }

hmWanMbus8DValue00		OBJECT-TYPE
			SYNTAX	INTEGER
			MAX-ACCESS	read-only
			STATUS	current
			::= { hmWanMbus8D 7 }

hmWanMbus8DVIF01		OBJECT-TYPE
			SYNTAX	INTEGER
			MAX-ACCESS	read-only
			STATUS	current
			::= { hmWanMbus8D 8 }

hmWanMbus8DValue01		OBJECT-TYPE
			SYNTAX	INTEGER
			MAX-ACCESS	read-only
			STATUS	current
			::= { hmWanMbus8D 9 }

hmWanMbus8DVIF02		OBJECT-TYPE
			SYNTAX	INTEGER
			MAX-ACCESS	read-only
			STATUS	current
			::= { hmWanMbus8D 10 }

hmWanMbus8DValue02		OBJECT-TYPE
			SYNTAX	INTEGER
			MAX-ACCESS	read-only
			STATUS	current
			::= { hmWanMbus8D 11 }

hmWanMbus8DVIF03		OBJECT-TYPE
			SYNTAX	INTEGER
			MAX-ACCESS	read-only
			STATUS	current
			::= { hmWanMbus8D 12 }

hmWanMbus8DValue03		OBJECT-TYPE
			SYNTAX	INTEGER
			MAX-ACCESS	read-only
			STATUS	current
			::= { hmWanMbus8D 13 }

hmWanMbus8DVIF04		OBJECT-TYPE
			SYNTAX	INTEGER
			MAX-ACCESS	read-only
			STATUS	current
			::= { hmWanMbus8D 14 }

hmWanMbus8DValue04		OBJECT-TYPE
			SYNTAX	INTEGER
			MAX-ACCESS	read-only
			STATUS	current
			::= { hmWanMbus8D 15 }

hmWanMbus8DVIF05		OBJECT-TYPE
			SYNTAX	INTEGER
			MAX-ACCESS	read-only
			STATUS	current
			::= { hmWanMbus8D 16 }

hmWanMbus8DValue05		OBJECT-TYPE
			SYNTAX	INTEGER
			MAX-ACCESS	read-only
			STATUS	current
			::= { hmWanMbus8D 17 }

hmWanMbus8DVIF06		OBJECT-TYPE
			SYNTAX	INTEGER
			MAX-ACCESS	read-only
			STATUS	current
			::= { hmWanMbus8D 18 }

hmWanMbus8DValue06		OBJECT-TYPE
			SYNTAX	INTEGER
			MAX-ACCESS	read-only
			STATUS	current
			::= { hmWanMbus8D 19 }

hmWanMbus8DVIF07		OBJECT-TYPE
			SYNTAX	INTEGER
			MAX-ACCESS	read-only
			STATUS	current
			::= { hmWanMbus8D 20 }

hmWanMbus8DValue07		OBJECT-TYPE
			SYNTAX	INTEGER
			MAX-ACCESS	read-only
			STATUS	current
			::= { hmWanMbus8D 21 }

hmWanMbus8DVIF08		OBJECT-TYPE
			SYNTAX	INTEGER
			MAX-ACCESS	read-only
			STATUS	current
			::= { hmWanMbus8D 22 }

hmWanMbus8DValue08		OBJECT-TYPE
			SYNTAX	INTEGER
			MAX-ACCESS	read-only
			STATUS	current
			::= { hmWanMbus8D 23 }

hmWanMbus8DVIF09		OBJECT-TYPE
			SYNTAX	INTEGER
			MAX-ACCESS	read-only
			STATUS	current
			::= { hmWanMbus8D 24 }

hmWanMbus8DValue09		OBJECT-TYPE
			SYNTAX	INTEGER
			MAX-ACCESS	read-only
			STATUS	current
			::= { hmWanMbus8D 25 }

hmWanMbus8DVIF0A		OBJECT-TYPE
			SYNTAX	INTEGER
			MAX-ACCESS	read-only
			STATUS	current
			::= { hmWanMbus8D 26 }

hmWanMbus8DValue0A		OBJECT-TYPE
			SYNTAX	INTEGER
			MAX-ACCESS	read-only
			STATUS	current
			::= { hmWanMbus8D 27 }

hmWanMbus8DVIF0B		OBJECT-TYPE
			SYNTAX	INTEGER
			MAX-ACCESS	read-only
			STATUS	current
			::= { hmWanMbus8D 28 }

hmWanMbus8DValue0B		OBJECT-TYPE
			SYNTAX	INTEGER
			MAX-ACCESS	read-only
			STATUS	current
			::= { hmWanMbus8D 29 }

hmWanMbus8DVIF0C		OBJECT-TYPE
			SYNTAX	INTEGER
			MAX-ACCESS	read-only
			STATUS	current
			::= { hmWanMbus8D 30 }

hmWanMbus8DValue0C		OBJECT-TYPE
			SYNTAX	INTEGER
			MAX-ACCESS	read-only
			STATUS	current
			::= { hmWanMbus8D 31 }

hmWanMbus8DVIF0D		OBJECT-TYPE
			SYNTAX	INTEGER
			MAX-ACCESS	read-only
			STATUS	current
			::= { hmWanMbus8D 32 }

hmWanMbus8DValue0D		OBJECT-TYPE
			SYNTAX	INTEGER
			MAX-ACCESS	read-only
			STATUS	current
			::= { hmWanMbus8D 33 }

hmWanMbus8DVIF0E		OBJECT-TYPE
			SYNTAX	INTEGER
			MAX-ACCESS	read-only
			STATUS	current
			::= { hmWanMbus8D 34 }

hmWanMbus8DValue0E		OBJECT-TYPE
			SYNTAX	INTEGER
			MAX-ACCESS	read-only
			STATUS	current
			::= { hmWanMbus8D 35 }

hmWanMbus8DVIF0F		OBJECT-TYPE
			SYNTAX	INTEGER
			MAX-ACCESS	read-only
			STATUS	current
			::= { hmWanMbus8D 36 }

hmWanMbus8DValue0F		OBJECT-TYPE
			SYNTAX	INTEGER
			MAX-ACCESS	read-only
			STATUS	current
			::= { hmWanMbus8D 37 }

hmWanMbus8DVIF10		OBJECT-TYPE
			SYNTAX	INTEGER
			MAX-ACCESS	read-only
			STATUS	current
			::= { hmWanMbus8D 38 }

hmWanMbus8DValue10		OBJECT-TYPE
			SYNTAX	INTEGER
			MAX-ACCESS	read-only
			STATUS	current
			::= { hmWanMbus8D 39 }

hmWanMbus8DVIF11		OBJECT-TYPE
			SYNTAX	INTEGER
			MAX-ACCESS	read-only
			STATUS	current
			::= { hmWanMbus8D 40 }

hmWanMbus8DValue11		OBJECT-TYPE
			SYNTAX	INTEGER
			MAX-ACCESS	read-only
			STATUS	current
			::= { hmWanMbus8D 41 }

hmWanMbus8DVIF12		OBJECT-TYPE
			SYNTAX	INTEGER
			MAX-ACCESS	read-only
			STATUS	current
			::= { hmWanMbus8D 42 }

hmWanMbus8DValue12		OBJECT-TYPE
			SYNTAX	INTEGER
			MAX-ACCESS	read-only
			STATUS	current
			::= { hmWanMbus8D 43 }

hmWanMbus8DVIF13		OBJECT-TYPE
			SYNTAX	INTEGER
			MAX-ACCESS	read-only
			STATUS	current
			::= { hmWanMbus8D 44 }

hmWanMbus8DValue13		OBJECT-TYPE
			SYNTAX	INTEGER
			MAX-ACCESS	read-only
			STATUS	current
			::= { hmWanMbus8D 45 }

hmWanMbus8DVIF14		OBJECT-TYPE
			SYNTAX	INTEGER
			MAX-ACCESS	read-only
			STATUS	current
			::= { hmWanMbus8D 46 }

hmWanMbus8DValue14		OBJECT-TYPE
			SYNTAX	INTEGER
			MAX-ACCESS	read-only
			STATUS	current
			::= { hmWanMbus8D 47 }

hmWanMbus8DVIF15		OBJECT-TYPE
			SYNTAX	INTEGER
			MAX-ACCESS	read-only
			STATUS	current
			::= { hmWanMbus8D 48 }

hmWanMbus8DValue15		OBJECT-TYPE
			SYNTAX	INTEGER
			MAX-ACCESS	read-only
			STATUS	current
			::= { hmWanMbus8D 49 }

hmWanMbus8DVIF16		OBJECT-TYPE
			SYNTAX	INTEGER
			MAX-ACCESS	read-only
			STATUS	current
			::= { hmWanMbus8D 50 }

hmWanMbus8DValue16		OBJECT-TYPE
			SYNTAX	INTEGER
			MAX-ACCESS	read-only
			STATUS	current
			::= { hmWanMbus8D 51 }

hmWanMbus8DVIF17		OBJECT-TYPE
			SYNTAX	INTEGER
			MAX-ACCESS	read-only
			STATUS	current
			::= { hmWanMbus8D 52 }

hmWanMbus8DValue17		OBJECT-TYPE
			SYNTAX	INTEGER
			MAX-ACCESS	read-only
			STATUS	current
			::= { hmWanMbus8D 53 }

hmWanMbus8DVIF18		OBJECT-TYPE
			SYNTAX	INTEGER
			MAX-ACCESS	read-only
			STATUS	current
			::= { hmWanMbus8D 54 }

hmWanMbus8DValue18		OBJECT-TYPE
			SYNTAX	INTEGER
			MAX-ACCESS	read-only
			STATUS	current
			::= { hmWanMbus8D 55 }

hmWanMbus8DVIF19		OBJECT-TYPE
			SYNTAX	INTEGER
			MAX-ACCESS	read-only
			STATUS	current
			::= { hmWanMbus8D 56 }

hmWanMbus8DValue19		OBJECT-TYPE
			SYNTAX	INTEGER
			MAX-ACCESS	read-only
			STATUS	current
			::= { hmWanMbus8D 57 }

hmWanMbus8DVIF1A		OBJECT-TYPE
			SYNTAX	INTEGER
			MAX-ACCESS	read-only
			STATUS	current
			::= { hmWanMbus8D 58 }

hmWanMbus8DValue1A		OBJECT-TYPE
			SYNTAX	INTEGER
			MAX-ACCESS	read-only
			STATUS	current
			::= { hmWanMbus8D 59 }

hmWanMbus8DVIF1B		OBJECT-TYPE
			SYNTAX	INTEGER
			MAX-ACCESS	read-only
			STATUS	current
			::= { hmWanMbus8D 60 }

hmWanMbus8DValue1B		OBJECT-TYPE
			SYNTAX	INTEGER
			MAX-ACCESS	read-only
			STATUS	current
			::= { hmWanMbus8D 61 }

hmWanMbus8DVIF1C		OBJECT-TYPE
			SYNTAX	INTEGER
			MAX-ACCESS	read-only
			STATUS	current
			::= { hmWanMbus8D 62 }

hmWanMbus8DValue1C		OBJECT-TYPE
			SYNTAX	INTEGER
			MAX-ACCESS	read-only
			STATUS	current
			::= { hmWanMbus8D 63 }

hmWanMbus8DVIF1D		OBJECT-TYPE
			SYNTAX	INTEGER
			MAX-ACCESS	read-only
			STATUS	current
			::= { hmWanMbus8D 64 }

hmWanMbus8DValue1D		OBJECT-TYPE
			SYNTAX	INTEGER
			MAX-ACCESS	read-only
			STATUS	current
			::= { hmWanMbus8D 65 }

hmWanMbus8DVIF1E		OBJECT-TYPE
			SYNTAX	INTEGER
			MAX-ACCESS	read-only
			STATUS	current
			::= { hmWanMbus8D 66 }

hmWanMbus8DValue1E		OBJECT-TYPE
			SYNTAX	INTEGER
			MAX-ACCESS	read-only
			STATUS	current
			::= { hmWanMbus8D 67 }

hmWanMbus8DVIF1F		OBJECT-TYPE
			SYNTAX	INTEGER
			MAX-ACCESS	read-only
			STATUS	current
			::= { hmWanMbus8D 68 }

hmWanMbus8DValue1F		OBJECT-TYPE
			SYNTAX	INTEGER
			MAX-ACCESS	read-only
			STATUS	current
			::= { hmWanMbus8D 69 }

hmWanMbus8DVIF20		OBJECT-TYPE
			SYNTAX	INTEGER
			MAX-ACCESS	read-only
			STATUS	current
			::= { hmWanMbus8D 70 }

hmWanMbus8DValue20		OBJECT-TYPE
			SYNTAX	INTEGER
			MAX-ACCESS	read-only
			STATUS	current
			::= { hmWanMbus8D 71 }

hmWanMbus8DVIF21		OBJECT-TYPE
			SYNTAX	INTEGER
			MAX-ACCESS	read-only
			STATUS	current
			::= { hmWanMbus8D 72 }

hmWanMbus8DValue21		OBJECT-TYPE
			SYNTAX	INTEGER
			MAX-ACCESS	read-only
			STATUS	current
			::= { hmWanMbus8D 73 }

hmWanMbus8DVIF22		OBJECT-TYPE
			SYNTAX	INTEGER
			MAX-ACCESS	read-only
			STATUS	current
			::= { hmWanMbus8D 74 }

hmWanMbus8DValue22		OBJECT-TYPE
			SYNTAX	INTEGER
			MAX-ACCESS	read-only
			STATUS	current
			::= { hmWanMbus8D 75 }

hmWanMbus8DVIF23		OBJECT-TYPE
			SYNTAX	INTEGER
			MAX-ACCESS	read-only
			STATUS	current
			::= { hmWanMbus8D 76 }

hmWanMbus8DValue23		OBJECT-TYPE
			SYNTAX	INTEGER
			MAX-ACCESS	read-only
			STATUS	current
			::= { hmWanMbus8D 77 }

hmWanMbus8DVIF24		OBJECT-TYPE
			SYNTAX	INTEGER
			MAX-ACCESS	read-only
			STATUS	current
			::= { hmWanMbus8D 78 }

hmWanMbus8DValue24		OBJECT-TYPE
			SYNTAX	INTEGER
			MAX-ACCESS	read-only
			STATUS	current
			::= { hmWanMbus8D 79 }

hmWanMbus8DVIF25		OBJECT-TYPE
			SYNTAX	INTEGER
			MAX-ACCESS	read-only
			STATUS	current
			::= { hmWanMbus8D 80 }

hmWanMbus8DValue25		OBJECT-TYPE
			SYNTAX	INTEGER
			MAX-ACCESS	read-only
			STATUS	current
			::= { hmWanMbus8D 81 }

hmWanMbus8DVIF26		OBJECT-TYPE
			SYNTAX	INTEGER
			MAX-ACCESS	read-only
			STATUS	current
			::= { hmWanMbus8D 82 }

hmWanMbus8DValue26		OBJECT-TYPE
			SYNTAX	INTEGER
			MAX-ACCESS	read-only
			STATUS	current
			::= { hmWanMbus8D 83 }

hmWanMbus8DVIF27		OBJECT-TYPE
			SYNTAX	INTEGER
			MAX-ACCESS	read-only
			STATUS	current
			::= { hmWanMbus8D 84 }

hmWanMbus8DValue27		OBJECT-TYPE
			SYNTAX	INTEGER
			MAX-ACCESS	read-only
			STATUS	current
			::= { hmWanMbus8D 85 }

hmWanMbus8DVIF28		OBJECT-TYPE
			SYNTAX	INTEGER
			MAX-ACCESS	read-only
			STATUS	current
			::= { hmWanMbus8D 86 }

hmWanMbus8DValue28		OBJECT-TYPE
			SYNTAX	INTEGER
			MAX-ACCESS	read-only
			STATUS	current
			::= { hmWanMbus8D 87 }

hmWanMbus8DVIF29		OBJECT-TYPE
			SYNTAX	INTEGER
			MAX-ACCESS	read-only
			STATUS	current
			::= { hmWanMbus8D 88 }

hmWanMbus8DValue29		OBJECT-TYPE
			SYNTAX	INTEGER
			MAX-ACCESS	read-only
			STATUS	current
			::= { hmWanMbus8D 89 }

hmWanMbus8DVIF2A		OBJECT-TYPE
			SYNTAX	INTEGER
			MAX-ACCESS	read-only
			STATUS	current
			::= { hmWanMbus8D 90 }

hmWanMbus8DValue2A		OBJECT-TYPE
			SYNTAX	INTEGER
			MAX-ACCESS	read-only
			STATUS	current
			::= { hmWanMbus8D 91 }

hmWanMbus8DVIF2B		OBJECT-TYPE
			SYNTAX	INTEGER
			MAX-ACCESS	read-only
			STATUS	current
			::= { hmWanMbus8D 92 }

hmWanMbus8DValue2B		OBJECT-TYPE
			SYNTAX	INTEGER
			MAX-ACCESS	read-only
			STATUS	current
			::= { hmWanMbus8D 93 }

hmWanMbus8DVIF2C		OBJECT-TYPE
			SYNTAX	INTEGER
			MAX-ACCESS	read-only
			STATUS	current
			::= { hmWanMbus8D 94 }

hmWanMbus8DValue2C		OBJECT-TYPE
			SYNTAX	INTEGER
			MAX-ACCESS	read-only
			STATUS	current
			::= { hmWanMbus8D 95 }

hmWanMbus8DVIF2D		OBJECT-TYPE
			SYNTAX	INTEGER
			MAX-ACCESS	read-only
			STATUS	current
			::= { hmWanMbus8D 96 }

hmWanMbus8DValue2D		OBJECT-TYPE
			SYNTAX	INTEGER
			MAX-ACCESS	read-only
			STATUS	current
			::= { hmWanMbus8D 97 }

hmWanMbus8DVIF2E		OBJECT-TYPE
			SYNTAX	INTEGER
			MAX-ACCESS	read-only
			STATUS	current
			::= { hmWanMbus8D 98 }

hmWanMbus8DValue2E		OBJECT-TYPE
			SYNTAX	INTEGER
			MAX-ACCESS	read-only
			STATUS	current
			::= { hmWanMbus8D 99 }

hmWanMbus8DVIF2F		OBJECT-TYPE
			SYNTAX	INTEGER
			MAX-ACCESS	read-only
			STATUS	current
			::= { hmWanMbus8D 100 }

hmWanMbus8DValue2F		OBJECT-TYPE
			SYNTAX	INTEGER
			MAX-ACCESS	read-only
			STATUS	current
			::= { hmWanMbus8D 101 }

hmWanMbus8E			OBJECT IDENTIFIER ::= { hmWanMbus 142 }

hmWanMbus8EIdNumber		OBJECT-TYPE
			SYNTAX	Gauge32
			MAX-ACCESS	read-only
			STATUS	current
			::= { hmWanMbus8E 1 }

hmWanMbus8EManufacturer	OBJECT-TYPE
			SYNTAX	Gauge32
			MAX-ACCESS	read-only
			STATUS	current
			::= { hmWanMbus8E 2 }

hmWanMbus8EVersion		OBJECT-TYPE
			SYNTAX	Gauge32
			MAX-ACCESS	read-only
			STATUS	current
			::= { hmWanMbus8E 3 }

hmWanMbus8EMedium		OBJECT-TYPE
			SYNTAX	Gauge32
			MAX-ACCESS	read-only
			STATUS	current
			::= { hmWanMbus8E 4 }

hmWanMbus8EStatus		OBJECT-TYPE
			SYNTAX	Gauge32
			MAX-ACCESS	read-only
			STATUS	current
			::= { hmWanMbus8E 5 }

hmWanMbus8EVIF00		OBJECT-TYPE
			SYNTAX	INTEGER
			MAX-ACCESS	read-only
			STATUS	current
			::= { hmWanMbus8E 6 }

hmWanMbus8EValue00		OBJECT-TYPE
			SYNTAX	INTEGER
			MAX-ACCESS	read-only
			STATUS	current
			::= { hmWanMbus8E 7 }

hmWanMbus8EVIF01		OBJECT-TYPE
			SYNTAX	INTEGER
			MAX-ACCESS	read-only
			STATUS	current
			::= { hmWanMbus8E 8 }

hmWanMbus8EValue01		OBJECT-TYPE
			SYNTAX	INTEGER
			MAX-ACCESS	read-only
			STATUS	current
			::= { hmWanMbus8E 9 }

hmWanMbus8EVIF02		OBJECT-TYPE
			SYNTAX	INTEGER
			MAX-ACCESS	read-only
			STATUS	current
			::= { hmWanMbus8E 10 }

hmWanMbus8EValue02		OBJECT-TYPE
			SYNTAX	INTEGER
			MAX-ACCESS	read-only
			STATUS	current
			::= { hmWanMbus8E 11 }

hmWanMbus8EVIF03		OBJECT-TYPE
			SYNTAX	INTEGER
			MAX-ACCESS	read-only
			STATUS	current
			::= { hmWanMbus8E 12 }

hmWanMbus8EValue03		OBJECT-TYPE
			SYNTAX	INTEGER
			MAX-ACCESS	read-only
			STATUS	current
			::= { hmWanMbus8E 13 }

hmWanMbus8EVIF04		OBJECT-TYPE
			SYNTAX	INTEGER
			MAX-ACCESS	read-only
			STATUS	current
			::= { hmWanMbus8E 14 }

hmWanMbus8EValue04		OBJECT-TYPE
			SYNTAX	INTEGER
			MAX-ACCESS	read-only
			STATUS	current
			::= { hmWanMbus8E 15 }

hmWanMbus8EVIF05		OBJECT-TYPE
			SYNTAX	INTEGER
			MAX-ACCESS	read-only
			STATUS	current
			::= { hmWanMbus8E 16 }

hmWanMbus8EValue05		OBJECT-TYPE
			SYNTAX	INTEGER
			MAX-ACCESS	read-only
			STATUS	current
			::= { hmWanMbus8E 17 }

hmWanMbus8EVIF06		OBJECT-TYPE
			SYNTAX	INTEGER
			MAX-ACCESS	read-only
			STATUS	current
			::= { hmWanMbus8E 18 }

hmWanMbus8EValue06		OBJECT-TYPE
			SYNTAX	INTEGER
			MAX-ACCESS	read-only
			STATUS	current
			::= { hmWanMbus8E 19 }

hmWanMbus8EVIF07		OBJECT-TYPE
			SYNTAX	INTEGER
			MAX-ACCESS	read-only
			STATUS	current
			::= { hmWanMbus8E 20 }

hmWanMbus8EValue07		OBJECT-TYPE
			SYNTAX	INTEGER
			MAX-ACCESS	read-only
			STATUS	current
			::= { hmWanMbus8E 21 }

hmWanMbus8EVIF08		OBJECT-TYPE
			SYNTAX	INTEGER
			MAX-ACCESS	read-only
			STATUS	current
			::= { hmWanMbus8E 22 }

hmWanMbus8EValue08		OBJECT-TYPE
			SYNTAX	INTEGER
			MAX-ACCESS	read-only
			STATUS	current
			::= { hmWanMbus8E 23 }

hmWanMbus8EVIF09		OBJECT-TYPE
			SYNTAX	INTEGER
			MAX-ACCESS	read-only
			STATUS	current
			::= { hmWanMbus8E 24 }

hmWanMbus8EValue09		OBJECT-TYPE
			SYNTAX	INTEGER
			MAX-ACCESS	read-only
			STATUS	current
			::= { hmWanMbus8E 25 }

hmWanMbus8EVIF0A		OBJECT-TYPE
			SYNTAX	INTEGER
			MAX-ACCESS	read-only
			STATUS	current
			::= { hmWanMbus8E 26 }

hmWanMbus8EValue0A		OBJECT-TYPE
			SYNTAX	INTEGER
			MAX-ACCESS	read-only
			STATUS	current
			::= { hmWanMbus8E 27 }

hmWanMbus8EVIF0B		OBJECT-TYPE
			SYNTAX	INTEGER
			MAX-ACCESS	read-only
			STATUS	current
			::= { hmWanMbus8E 28 }

hmWanMbus8EValue0B		OBJECT-TYPE
			SYNTAX	INTEGER
			MAX-ACCESS	read-only
			STATUS	current
			::= { hmWanMbus8E 29 }

hmWanMbus8EVIF0C		OBJECT-TYPE
			SYNTAX	INTEGER
			MAX-ACCESS	read-only
			STATUS	current
			::= { hmWanMbus8E 30 }

hmWanMbus8EValue0C		OBJECT-TYPE
			SYNTAX	INTEGER
			MAX-ACCESS	read-only
			STATUS	current
			::= { hmWanMbus8E 31 }

hmWanMbus8EVIF0D		OBJECT-TYPE
			SYNTAX	INTEGER
			MAX-ACCESS	read-only
			STATUS	current
			::= { hmWanMbus8E 32 }

hmWanMbus8EValue0D		OBJECT-TYPE
			SYNTAX	INTEGER
			MAX-ACCESS	read-only
			STATUS	current
			::= { hmWanMbus8E 33 }

hmWanMbus8EVIF0E		OBJECT-TYPE
			SYNTAX	INTEGER
			MAX-ACCESS	read-only
			STATUS	current
			::= { hmWanMbus8E 34 }

hmWanMbus8EValue0E		OBJECT-TYPE
			SYNTAX	INTEGER
			MAX-ACCESS	read-only
			STATUS	current
			::= { hmWanMbus8E 35 }

hmWanMbus8EVIF0F		OBJECT-TYPE
			SYNTAX	INTEGER
			MAX-ACCESS	read-only
			STATUS	current
			::= { hmWanMbus8E 36 }

hmWanMbus8EValue0F		OBJECT-TYPE
			SYNTAX	INTEGER
			MAX-ACCESS	read-only
			STATUS	current
			::= { hmWanMbus8E 37 }

hmWanMbus8EVIF10		OBJECT-TYPE
			SYNTAX	INTEGER
			MAX-ACCESS	read-only
			STATUS	current
			::= { hmWanMbus8E 38 }

hmWanMbus8EValue10		OBJECT-TYPE
			SYNTAX	INTEGER
			MAX-ACCESS	read-only
			STATUS	current
			::= { hmWanMbus8E 39 }

hmWanMbus8EVIF11		OBJECT-TYPE
			SYNTAX	INTEGER
			MAX-ACCESS	read-only
			STATUS	current
			::= { hmWanMbus8E 40 }

hmWanMbus8EValue11		OBJECT-TYPE
			SYNTAX	INTEGER
			MAX-ACCESS	read-only
			STATUS	current
			::= { hmWanMbus8E 41 }

hmWanMbus8EVIF12		OBJECT-TYPE
			SYNTAX	INTEGER
			MAX-ACCESS	read-only
			STATUS	current
			::= { hmWanMbus8E 42 }

hmWanMbus8EValue12		OBJECT-TYPE
			SYNTAX	INTEGER
			MAX-ACCESS	read-only
			STATUS	current
			::= { hmWanMbus8E 43 }

hmWanMbus8EVIF13		OBJECT-TYPE
			SYNTAX	INTEGER
			MAX-ACCESS	read-only
			STATUS	current
			::= { hmWanMbus8E 44 }

hmWanMbus8EValue13		OBJECT-TYPE
			SYNTAX	INTEGER
			MAX-ACCESS	read-only
			STATUS	current
			::= { hmWanMbus8E 45 }

hmWanMbus8EVIF14		OBJECT-TYPE
			SYNTAX	INTEGER
			MAX-ACCESS	read-only
			STATUS	current
			::= { hmWanMbus8E 46 }

hmWanMbus8EValue14		OBJECT-TYPE
			SYNTAX	INTEGER
			MAX-ACCESS	read-only
			STATUS	current
			::= { hmWanMbus8E 47 }

hmWanMbus8EVIF15		OBJECT-TYPE
			SYNTAX	INTEGER
			MAX-ACCESS	read-only
			STATUS	current
			::= { hmWanMbus8E 48 }

hmWanMbus8EValue15		OBJECT-TYPE
			SYNTAX	INTEGER
			MAX-ACCESS	read-only
			STATUS	current
			::= { hmWanMbus8E 49 }

hmWanMbus8EVIF16		OBJECT-TYPE
			SYNTAX	INTEGER
			MAX-ACCESS	read-only
			STATUS	current
			::= { hmWanMbus8E 50 }

hmWanMbus8EValue16		OBJECT-TYPE
			SYNTAX	INTEGER
			MAX-ACCESS	read-only
			STATUS	current
			::= { hmWanMbus8E 51 }

hmWanMbus8EVIF17		OBJECT-TYPE
			SYNTAX	INTEGER
			MAX-ACCESS	read-only
			STATUS	current
			::= { hmWanMbus8E 52 }

hmWanMbus8EValue17		OBJECT-TYPE
			SYNTAX	INTEGER
			MAX-ACCESS	read-only
			STATUS	current
			::= { hmWanMbus8E 53 }

hmWanMbus8EVIF18		OBJECT-TYPE
			SYNTAX	INTEGER
			MAX-ACCESS	read-only
			STATUS	current
			::= { hmWanMbus8E 54 }

hmWanMbus8EValue18		OBJECT-TYPE
			SYNTAX	INTEGER
			MAX-ACCESS	read-only
			STATUS	current
			::= { hmWanMbus8E 55 }

hmWanMbus8EVIF19		OBJECT-TYPE
			SYNTAX	INTEGER
			MAX-ACCESS	read-only
			STATUS	current
			::= { hmWanMbus8E 56 }

hmWanMbus8EValue19		OBJECT-TYPE
			SYNTAX	INTEGER
			MAX-ACCESS	read-only
			STATUS	current
			::= { hmWanMbus8E 57 }

hmWanMbus8EVIF1A		OBJECT-TYPE
			SYNTAX	INTEGER
			MAX-ACCESS	read-only
			STATUS	current
			::= { hmWanMbus8E 58 }

hmWanMbus8EValue1A		OBJECT-TYPE
			SYNTAX	INTEGER
			MAX-ACCESS	read-only
			STATUS	current
			::= { hmWanMbus8E 59 }

hmWanMbus8EVIF1B		OBJECT-TYPE
			SYNTAX	INTEGER
			MAX-ACCESS	read-only
			STATUS	current
			::= { hmWanMbus8E 60 }

hmWanMbus8EValue1B		OBJECT-TYPE
			SYNTAX	INTEGER
			MAX-ACCESS	read-only
			STATUS	current
			::= { hmWanMbus8E 61 }

hmWanMbus8EVIF1C		OBJECT-TYPE
			SYNTAX	INTEGER
			MAX-ACCESS	read-only
			STATUS	current
			::= { hmWanMbus8E 62 }

hmWanMbus8EValue1C		OBJECT-TYPE
			SYNTAX	INTEGER
			MAX-ACCESS	read-only
			STATUS	current
			::= { hmWanMbus8E 63 }

hmWanMbus8EVIF1D		OBJECT-TYPE
			SYNTAX	INTEGER
			MAX-ACCESS	read-only
			STATUS	current
			::= { hmWanMbus8E 64 }

hmWanMbus8EValue1D		OBJECT-TYPE
			SYNTAX	INTEGER
			MAX-ACCESS	read-only
			STATUS	current
			::= { hmWanMbus8E 65 }

hmWanMbus8EVIF1E		OBJECT-TYPE
			SYNTAX	INTEGER
			MAX-ACCESS	read-only
			STATUS	current
			::= { hmWanMbus8E 66 }

hmWanMbus8EValue1E		OBJECT-TYPE
			SYNTAX	INTEGER
			MAX-ACCESS	read-only
			STATUS	current
			::= { hmWanMbus8E 67 }

hmWanMbus8EVIF1F		OBJECT-TYPE
			SYNTAX	INTEGER
			MAX-ACCESS	read-only
			STATUS	current
			::= { hmWanMbus8E 68 }

hmWanMbus8EValue1F		OBJECT-TYPE
			SYNTAX	INTEGER
			MAX-ACCESS	read-only
			STATUS	current
			::= { hmWanMbus8E 69 }

hmWanMbus8EVIF20		OBJECT-TYPE
			SYNTAX	INTEGER
			MAX-ACCESS	read-only
			STATUS	current
			::= { hmWanMbus8E 70 }

hmWanMbus8EValue20		OBJECT-TYPE
			SYNTAX	INTEGER
			MAX-ACCESS	read-only
			STATUS	current
			::= { hmWanMbus8E 71 }

hmWanMbus8EVIF21		OBJECT-TYPE
			SYNTAX	INTEGER
			MAX-ACCESS	read-only
			STATUS	current
			::= { hmWanMbus8E 72 }

hmWanMbus8EValue21		OBJECT-TYPE
			SYNTAX	INTEGER
			MAX-ACCESS	read-only
			STATUS	current
			::= { hmWanMbus8E 73 }

hmWanMbus8EVIF22		OBJECT-TYPE
			SYNTAX	INTEGER
			MAX-ACCESS	read-only
			STATUS	current
			::= { hmWanMbus8E 74 }

hmWanMbus8EValue22		OBJECT-TYPE
			SYNTAX	INTEGER
			MAX-ACCESS	read-only
			STATUS	current
			::= { hmWanMbus8E 75 }

hmWanMbus8EVIF23		OBJECT-TYPE
			SYNTAX	INTEGER
			MAX-ACCESS	read-only
			STATUS	current
			::= { hmWanMbus8E 76 }

hmWanMbus8EValue23		OBJECT-TYPE
			SYNTAX	INTEGER
			MAX-ACCESS	read-only
			STATUS	current
			::= { hmWanMbus8E 77 }

hmWanMbus8EVIF24		OBJECT-TYPE
			SYNTAX	INTEGER
			MAX-ACCESS	read-only
			STATUS	current
			::= { hmWanMbus8E 78 }

hmWanMbus8EValue24		OBJECT-TYPE
			SYNTAX	INTEGER
			MAX-ACCESS	read-only
			STATUS	current
			::= { hmWanMbus8E 79 }

hmWanMbus8EVIF25		OBJECT-TYPE
			SYNTAX	INTEGER
			MAX-ACCESS	read-only
			STATUS	current
			::= { hmWanMbus8E 80 }

hmWanMbus8EValue25		OBJECT-TYPE
			SYNTAX	INTEGER
			MAX-ACCESS	read-only
			STATUS	current
			::= { hmWanMbus8E 81 }

hmWanMbus8EVIF26		OBJECT-TYPE
			SYNTAX	INTEGER
			MAX-ACCESS	read-only
			STATUS	current
			::= { hmWanMbus8E 82 }

hmWanMbus8EValue26		OBJECT-TYPE
			SYNTAX	INTEGER
			MAX-ACCESS	read-only
			STATUS	current
			::= { hmWanMbus8E 83 }

hmWanMbus8EVIF27		OBJECT-TYPE
			SYNTAX	INTEGER
			MAX-ACCESS	read-only
			STATUS	current
			::= { hmWanMbus8E 84 }

hmWanMbus8EValue27		OBJECT-TYPE
			SYNTAX	INTEGER
			MAX-ACCESS	read-only
			STATUS	current
			::= { hmWanMbus8E 85 }

hmWanMbus8EVIF28		OBJECT-TYPE
			SYNTAX	INTEGER
			MAX-ACCESS	read-only
			STATUS	current
			::= { hmWanMbus8E 86 }

hmWanMbus8EValue28		OBJECT-TYPE
			SYNTAX	INTEGER
			MAX-ACCESS	read-only
			STATUS	current
			::= { hmWanMbus8E 87 }

hmWanMbus8EVIF29		OBJECT-TYPE
			SYNTAX	INTEGER
			MAX-ACCESS	read-only
			STATUS	current
			::= { hmWanMbus8E 88 }

hmWanMbus8EValue29		OBJECT-TYPE
			SYNTAX	INTEGER
			MAX-ACCESS	read-only
			STATUS	current
			::= { hmWanMbus8E 89 }

hmWanMbus8EVIF2A		OBJECT-TYPE
			SYNTAX	INTEGER
			MAX-ACCESS	read-only
			STATUS	current
			::= { hmWanMbus8E 90 }

hmWanMbus8EValue2A		OBJECT-TYPE
			SYNTAX	INTEGER
			MAX-ACCESS	read-only
			STATUS	current
			::= { hmWanMbus8E 91 }

hmWanMbus8EVIF2B		OBJECT-TYPE
			SYNTAX	INTEGER
			MAX-ACCESS	read-only
			STATUS	current
			::= { hmWanMbus8E 92 }

hmWanMbus8EValue2B		OBJECT-TYPE
			SYNTAX	INTEGER
			MAX-ACCESS	read-only
			STATUS	current
			::= { hmWanMbus8E 93 }

hmWanMbus8EVIF2C		OBJECT-TYPE
			SYNTAX	INTEGER
			MAX-ACCESS	read-only
			STATUS	current
			::= { hmWanMbus8E 94 }

hmWanMbus8EValue2C		OBJECT-TYPE
			SYNTAX	INTEGER
			MAX-ACCESS	read-only
			STATUS	current
			::= { hmWanMbus8E 95 }

hmWanMbus8EVIF2D		OBJECT-TYPE
			SYNTAX	INTEGER
			MAX-ACCESS	read-only
			STATUS	current
			::= { hmWanMbus8E 96 }

hmWanMbus8EValue2D		OBJECT-TYPE
			SYNTAX	INTEGER
			MAX-ACCESS	read-only
			STATUS	current
			::= { hmWanMbus8E 97 }

hmWanMbus8EVIF2E		OBJECT-TYPE
			SYNTAX	INTEGER
			MAX-ACCESS	read-only
			STATUS	current
			::= { hmWanMbus8E 98 }

hmWanMbus8EValue2E		OBJECT-TYPE
			SYNTAX	INTEGER
			MAX-ACCESS	read-only
			STATUS	current
			::= { hmWanMbus8E 99 }

hmWanMbus8EVIF2F		OBJECT-TYPE
			SYNTAX	INTEGER
			MAX-ACCESS	read-only
			STATUS	current
			::= { hmWanMbus8E 100 }

hmWanMbus8EValue2F		OBJECT-TYPE
			SYNTAX	INTEGER
			MAX-ACCESS	read-only
			STATUS	current
			::= { hmWanMbus8E 101 }

hmWanMbus8F			OBJECT IDENTIFIER ::= { hmWanMbus 143 }

hmWanMbus8FIdNumber		OBJECT-TYPE
			SYNTAX	Gauge32
			MAX-ACCESS	read-only
			STATUS	current
			::= { hmWanMbus8F 1 }

hmWanMbus8FManufacturer	OBJECT-TYPE
			SYNTAX	Gauge32
			MAX-ACCESS	read-only
			STATUS	current
			::= { hmWanMbus8F 2 }

hmWanMbus8FVersion		OBJECT-TYPE
			SYNTAX	Gauge32
			MAX-ACCESS	read-only
			STATUS	current
			::= { hmWanMbus8F 3 }

hmWanMbus8FMedium		OBJECT-TYPE
			SYNTAX	Gauge32
			MAX-ACCESS	read-only
			STATUS	current
			::= { hmWanMbus8F 4 }

hmWanMbus8FStatus		OBJECT-TYPE
			SYNTAX	Gauge32
			MAX-ACCESS	read-only
			STATUS	current
			::= { hmWanMbus8F 5 }

hmWanMbus8FVIF00		OBJECT-TYPE
			SYNTAX	INTEGER
			MAX-ACCESS	read-only
			STATUS	current
			::= { hmWanMbus8F 6 }

hmWanMbus8FValue00		OBJECT-TYPE
			SYNTAX	INTEGER
			MAX-ACCESS	read-only
			STATUS	current
			::= { hmWanMbus8F 7 }

hmWanMbus8FVIF01		OBJECT-TYPE
			SYNTAX	INTEGER
			MAX-ACCESS	read-only
			STATUS	current
			::= { hmWanMbus8F 8 }

hmWanMbus8FValue01		OBJECT-TYPE
			SYNTAX	INTEGER
			MAX-ACCESS	read-only
			STATUS	current
			::= { hmWanMbus8F 9 }

hmWanMbus8FVIF02		OBJECT-TYPE
			SYNTAX	INTEGER
			MAX-ACCESS	read-only
			STATUS	current
			::= { hmWanMbus8F 10 }

hmWanMbus8FValue02		OBJECT-TYPE
			SYNTAX	INTEGER
			MAX-ACCESS	read-only
			STATUS	current
			::= { hmWanMbus8F 11 }

hmWanMbus8FVIF03		OBJECT-TYPE
			SYNTAX	INTEGER
			MAX-ACCESS	read-only
			STATUS	current
			::= { hmWanMbus8F 12 }

hmWanMbus8FValue03		OBJECT-TYPE
			SYNTAX	INTEGER
			MAX-ACCESS	read-only
			STATUS	current
			::= { hmWanMbus8F 13 }

hmWanMbus8FVIF04		OBJECT-TYPE
			SYNTAX	INTEGER
			MAX-ACCESS	read-only
			STATUS	current
			::= { hmWanMbus8F 14 }

hmWanMbus8FValue04		OBJECT-TYPE
			SYNTAX	INTEGER
			MAX-ACCESS	read-only
			STATUS	current
			::= { hmWanMbus8F 15 }

hmWanMbus8FVIF05		OBJECT-TYPE
			SYNTAX	INTEGER
			MAX-ACCESS	read-only
			STATUS	current
			::= { hmWanMbus8F 16 }

hmWanMbus8FValue05		OBJECT-TYPE
			SYNTAX	INTEGER
			MAX-ACCESS	read-only
			STATUS	current
			::= { hmWanMbus8F 17 }

hmWanMbus8FVIF06		OBJECT-TYPE
			SYNTAX	INTEGER
			MAX-ACCESS	read-only
			STATUS	current
			::= { hmWanMbus8F 18 }

hmWanMbus8FValue06		OBJECT-TYPE
			SYNTAX	INTEGER
			MAX-ACCESS	read-only
			STATUS	current
			::= { hmWanMbus8F 19 }

hmWanMbus8FVIF07		OBJECT-TYPE
			SYNTAX	INTEGER
			MAX-ACCESS	read-only
			STATUS	current
			::= { hmWanMbus8F 20 }

hmWanMbus8FValue07		OBJECT-TYPE
			SYNTAX	INTEGER
			MAX-ACCESS	read-only
			STATUS	current
			::= { hmWanMbus8F 21 }

hmWanMbus8FVIF08		OBJECT-TYPE
			SYNTAX	INTEGER
			MAX-ACCESS	read-only
			STATUS	current
			::= { hmWanMbus8F 22 }

hmWanMbus8FValue08		OBJECT-TYPE
			SYNTAX	INTEGER
			MAX-ACCESS	read-only
			STATUS	current
			::= { hmWanMbus8F 23 }

hmWanMbus8FVIF09		OBJECT-TYPE
			SYNTAX	INTEGER
			MAX-ACCESS	read-only
			STATUS	current
			::= { hmWanMbus8F 24 }

hmWanMbus8FValue09		OBJECT-TYPE
			SYNTAX	INTEGER
			MAX-ACCESS	read-only
			STATUS	current
			::= { hmWanMbus8F 25 }

hmWanMbus8FVIF0A		OBJECT-TYPE
			SYNTAX	INTEGER
			MAX-ACCESS	read-only
			STATUS	current
			::= { hmWanMbus8F 26 }

hmWanMbus8FValue0A		OBJECT-TYPE
			SYNTAX	INTEGER
			MAX-ACCESS	read-only
			STATUS	current
			::= { hmWanMbus8F 27 }

hmWanMbus8FVIF0B		OBJECT-TYPE
			SYNTAX	INTEGER
			MAX-ACCESS	read-only
			STATUS	current
			::= { hmWanMbus8F 28 }

hmWanMbus8FValue0B		OBJECT-TYPE
			SYNTAX	INTEGER
			MAX-ACCESS	read-only
			STATUS	current
			::= { hmWanMbus8F 29 }

hmWanMbus8FVIF0C		OBJECT-TYPE
			SYNTAX	INTEGER
			MAX-ACCESS	read-only
			STATUS	current
			::= { hmWanMbus8F 30 }

hmWanMbus8FValue0C		OBJECT-TYPE
			SYNTAX	INTEGER
			MAX-ACCESS	read-only
			STATUS	current
			::= { hmWanMbus8F 31 }

hmWanMbus8FVIF0D		OBJECT-TYPE
			SYNTAX	INTEGER
			MAX-ACCESS	read-only
			STATUS	current
			::= { hmWanMbus8F 32 }

hmWanMbus8FValue0D		OBJECT-TYPE
			SYNTAX	INTEGER
			MAX-ACCESS	read-only
			STATUS	current
			::= { hmWanMbus8F 33 }

hmWanMbus8FVIF0E		OBJECT-TYPE
			SYNTAX	INTEGER
			MAX-ACCESS	read-only
			STATUS	current
			::= { hmWanMbus8F 34 }

hmWanMbus8FValue0E		OBJECT-TYPE
			SYNTAX	INTEGER
			MAX-ACCESS	read-only
			STATUS	current
			::= { hmWanMbus8F 35 }

hmWanMbus8FVIF0F		OBJECT-TYPE
			SYNTAX	INTEGER
			MAX-ACCESS	read-only
			STATUS	current
			::= { hmWanMbus8F 36 }

hmWanMbus8FValue0F		OBJECT-TYPE
			SYNTAX	INTEGER
			MAX-ACCESS	read-only
			STATUS	current
			::= { hmWanMbus8F 37 }

hmWanMbus8FVIF10		OBJECT-TYPE
			SYNTAX	INTEGER
			MAX-ACCESS	read-only
			STATUS	current
			::= { hmWanMbus8F 38 }

hmWanMbus8FValue10		OBJECT-TYPE
			SYNTAX	INTEGER
			MAX-ACCESS	read-only
			STATUS	current
			::= { hmWanMbus8F 39 }

hmWanMbus8FVIF11		OBJECT-TYPE
			SYNTAX	INTEGER
			MAX-ACCESS	read-only
			STATUS	current
			::= { hmWanMbus8F 40 }

hmWanMbus8FValue11		OBJECT-TYPE
			SYNTAX	INTEGER
			MAX-ACCESS	read-only
			STATUS	current
			::= { hmWanMbus8F 41 }

hmWanMbus8FVIF12		OBJECT-TYPE
			SYNTAX	INTEGER
			MAX-ACCESS	read-only
			STATUS	current
			::= { hmWanMbus8F 42 }

hmWanMbus8FValue12		OBJECT-TYPE
			SYNTAX	INTEGER
			MAX-ACCESS	read-only
			STATUS	current
			::= { hmWanMbus8F 43 }

hmWanMbus8FVIF13		OBJECT-TYPE
			SYNTAX	INTEGER
			MAX-ACCESS	read-only
			STATUS	current
			::= { hmWanMbus8F 44 }

hmWanMbus8FValue13		OBJECT-TYPE
			SYNTAX	INTEGER
			MAX-ACCESS	read-only
			STATUS	current
			::= { hmWanMbus8F 45 }

hmWanMbus8FVIF14		OBJECT-TYPE
			SYNTAX	INTEGER
			MAX-ACCESS	read-only
			STATUS	current
			::= { hmWanMbus8F 46 }

hmWanMbus8FValue14		OBJECT-TYPE
			SYNTAX	INTEGER
			MAX-ACCESS	read-only
			STATUS	current
			::= { hmWanMbus8F 47 }

hmWanMbus8FVIF15		OBJECT-TYPE
			SYNTAX	INTEGER
			MAX-ACCESS	read-only
			STATUS	current
			::= { hmWanMbus8F 48 }

hmWanMbus8FValue15		OBJECT-TYPE
			SYNTAX	INTEGER
			MAX-ACCESS	read-only
			STATUS	current
			::= { hmWanMbus8F 49 }

hmWanMbus8FVIF16		OBJECT-TYPE
			SYNTAX	INTEGER
			MAX-ACCESS	read-only
			STATUS	current
			::= { hmWanMbus8F 50 }

hmWanMbus8FValue16		OBJECT-TYPE
			SYNTAX	INTEGER
			MAX-ACCESS	read-only
			STATUS	current
			::= { hmWanMbus8F 51 }

hmWanMbus8FVIF17		OBJECT-TYPE
			SYNTAX	INTEGER
			MAX-ACCESS	read-only
			STATUS	current
			::= { hmWanMbus8F 52 }

hmWanMbus8FValue17		OBJECT-TYPE
			SYNTAX	INTEGER
			MAX-ACCESS	read-only
			STATUS	current
			::= { hmWanMbus8F 53 }

hmWanMbus8FVIF18		OBJECT-TYPE
			SYNTAX	INTEGER
			MAX-ACCESS	read-only
			STATUS	current
			::= { hmWanMbus8F 54 }

hmWanMbus8FValue18		OBJECT-TYPE
			SYNTAX	INTEGER
			MAX-ACCESS	read-only
			STATUS	current
			::= { hmWanMbus8F 55 }

hmWanMbus8FVIF19		OBJECT-TYPE
			SYNTAX	INTEGER
			MAX-ACCESS	read-only
			STATUS	current
			::= { hmWanMbus8F 56 }

hmWanMbus8FValue19		OBJECT-TYPE
			SYNTAX	INTEGER
			MAX-ACCESS	read-only
			STATUS	current
			::= { hmWanMbus8F 57 }

hmWanMbus8FVIF1A		OBJECT-TYPE
			SYNTAX	INTEGER
			MAX-ACCESS	read-only
			STATUS	current
			::= { hmWanMbus8F 58 }

hmWanMbus8FValue1A		OBJECT-TYPE
			SYNTAX	INTEGER
			MAX-ACCESS	read-only
			STATUS	current
			::= { hmWanMbus8F 59 }

hmWanMbus8FVIF1B		OBJECT-TYPE
			SYNTAX	INTEGER
			MAX-ACCESS	read-only
			STATUS	current
			::= { hmWanMbus8F 60 }

hmWanMbus8FValue1B		OBJECT-TYPE
			SYNTAX	INTEGER
			MAX-ACCESS	read-only
			STATUS	current
			::= { hmWanMbus8F 61 }

hmWanMbus8FVIF1C		OBJECT-TYPE
			SYNTAX	INTEGER
			MAX-ACCESS	read-only
			STATUS	current
			::= { hmWanMbus8F 62 }

hmWanMbus8FValue1C		OBJECT-TYPE
			SYNTAX	INTEGER
			MAX-ACCESS	read-only
			STATUS	current
			::= { hmWanMbus8F 63 }

hmWanMbus8FVIF1D		OBJECT-TYPE
			SYNTAX	INTEGER
			MAX-ACCESS	read-only
			STATUS	current
			::= { hmWanMbus8F 64 }

hmWanMbus8FValue1D		OBJECT-TYPE
			SYNTAX	INTEGER
			MAX-ACCESS	read-only
			STATUS	current
			::= { hmWanMbus8F 65 }

hmWanMbus8FVIF1E		OBJECT-TYPE
			SYNTAX	INTEGER
			MAX-ACCESS	read-only
			STATUS	current
			::= { hmWanMbus8F 66 }

hmWanMbus8FValue1E		OBJECT-TYPE
			SYNTAX	INTEGER
			MAX-ACCESS	read-only
			STATUS	current
			::= { hmWanMbus8F 67 }

hmWanMbus8FVIF1F		OBJECT-TYPE
			SYNTAX	INTEGER
			MAX-ACCESS	read-only
			STATUS	current
			::= { hmWanMbus8F 68 }

hmWanMbus8FValue1F		OBJECT-TYPE
			SYNTAX	INTEGER
			MAX-ACCESS	read-only
			STATUS	current
			::= { hmWanMbus8F 69 }

hmWanMbus8FVIF20		OBJECT-TYPE
			SYNTAX	INTEGER
			MAX-ACCESS	read-only
			STATUS	current
			::= { hmWanMbus8F 70 }

hmWanMbus8FValue20		OBJECT-TYPE
			SYNTAX	INTEGER
			MAX-ACCESS	read-only
			STATUS	current
			::= { hmWanMbus8F 71 }

hmWanMbus8FVIF21		OBJECT-TYPE
			SYNTAX	INTEGER
			MAX-ACCESS	read-only
			STATUS	current
			::= { hmWanMbus8F 72 }

hmWanMbus8FValue21		OBJECT-TYPE
			SYNTAX	INTEGER
			MAX-ACCESS	read-only
			STATUS	current
			::= { hmWanMbus8F 73 }

hmWanMbus8FVIF22		OBJECT-TYPE
			SYNTAX	INTEGER
			MAX-ACCESS	read-only
			STATUS	current
			::= { hmWanMbus8F 74 }

hmWanMbus8FValue22		OBJECT-TYPE
			SYNTAX	INTEGER
			MAX-ACCESS	read-only
			STATUS	current
			::= { hmWanMbus8F 75 }

hmWanMbus8FVIF23		OBJECT-TYPE
			SYNTAX	INTEGER
			MAX-ACCESS	read-only
			STATUS	current
			::= { hmWanMbus8F 76 }

hmWanMbus8FValue23		OBJECT-TYPE
			SYNTAX	INTEGER
			MAX-ACCESS	read-only
			STATUS	current
			::= { hmWanMbus8F 77 }

hmWanMbus8FVIF24		OBJECT-TYPE
			SYNTAX	INTEGER
			MAX-ACCESS	read-only
			STATUS	current
			::= { hmWanMbus8F 78 }

hmWanMbus8FValue24		OBJECT-TYPE
			SYNTAX	INTEGER
			MAX-ACCESS	read-only
			STATUS	current
			::= { hmWanMbus8F 79 }

hmWanMbus8FVIF25		OBJECT-TYPE
			SYNTAX	INTEGER
			MAX-ACCESS	read-only
			STATUS	current
			::= { hmWanMbus8F 80 }

hmWanMbus8FValue25		OBJECT-TYPE
			SYNTAX	INTEGER
			MAX-ACCESS	read-only
			STATUS	current
			::= { hmWanMbus8F 81 }

hmWanMbus8FVIF26		OBJECT-TYPE
			SYNTAX	INTEGER
			MAX-ACCESS	read-only
			STATUS	current
			::= { hmWanMbus8F 82 }

hmWanMbus8FValue26		OBJECT-TYPE
			SYNTAX	INTEGER
			MAX-ACCESS	read-only
			STATUS	current
			::= { hmWanMbus8F 83 }

hmWanMbus8FVIF27		OBJECT-TYPE
			SYNTAX	INTEGER
			MAX-ACCESS	read-only
			STATUS	current
			::= { hmWanMbus8F 84 }

hmWanMbus8FValue27		OBJECT-TYPE
			SYNTAX	INTEGER
			MAX-ACCESS	read-only
			STATUS	current
			::= { hmWanMbus8F 85 }

hmWanMbus8FVIF28		OBJECT-TYPE
			SYNTAX	INTEGER
			MAX-ACCESS	read-only
			STATUS	current
			::= { hmWanMbus8F 86 }

hmWanMbus8FValue28		OBJECT-TYPE
			SYNTAX	INTEGER
			MAX-ACCESS	read-only
			STATUS	current
			::= { hmWanMbus8F 87 }

hmWanMbus8FVIF29		OBJECT-TYPE
			SYNTAX	INTEGER
			MAX-ACCESS	read-only
			STATUS	current
			::= { hmWanMbus8F 88 }

hmWanMbus8FValue29		OBJECT-TYPE
			SYNTAX	INTEGER
			MAX-ACCESS	read-only
			STATUS	current
			::= { hmWanMbus8F 89 }

hmWanMbus8FVIF2A		OBJECT-TYPE
			SYNTAX	INTEGER
			MAX-ACCESS	read-only
			STATUS	current
			::= { hmWanMbus8F 90 }

hmWanMbus8FValue2A		OBJECT-TYPE
			SYNTAX	INTEGER
			MAX-ACCESS	read-only
			STATUS	current
			::= { hmWanMbus8F 91 }

hmWanMbus8FVIF2B		OBJECT-TYPE
			SYNTAX	INTEGER
			MAX-ACCESS	read-only
			STATUS	current
			::= { hmWanMbus8F 92 }

hmWanMbus8FValue2B		OBJECT-TYPE
			SYNTAX	INTEGER
			MAX-ACCESS	read-only
			STATUS	current
			::= { hmWanMbus8F 93 }

hmWanMbus8FVIF2C		OBJECT-TYPE
			SYNTAX	INTEGER
			MAX-ACCESS	read-only
			STATUS	current
			::= { hmWanMbus8F 94 }

hmWanMbus8FValue2C		OBJECT-TYPE
			SYNTAX	INTEGER
			MAX-ACCESS	read-only
			STATUS	current
			::= { hmWanMbus8F 95 }

hmWanMbus8FVIF2D		OBJECT-TYPE
			SYNTAX	INTEGER
			MAX-ACCESS	read-only
			STATUS	current
			::= { hmWanMbus8F 96 }

hmWanMbus8FValue2D		OBJECT-TYPE
			SYNTAX	INTEGER
			MAX-ACCESS	read-only
			STATUS	current
			::= { hmWanMbus8F 97 }

hmWanMbus8FVIF2E		OBJECT-TYPE
			SYNTAX	INTEGER
			MAX-ACCESS	read-only
			STATUS	current
			::= { hmWanMbus8F 98 }

hmWanMbus8FValue2E		OBJECT-TYPE
			SYNTAX	INTEGER
			MAX-ACCESS	read-only
			STATUS	current
			::= { hmWanMbus8F 99 }

hmWanMbus8FVIF2F		OBJECT-TYPE
			SYNTAX	INTEGER
			MAX-ACCESS	read-only
			STATUS	current
			::= { hmWanMbus8F 100 }

hmWanMbus8FValue2F		OBJECT-TYPE
			SYNTAX	INTEGER
			MAX-ACCESS	read-only
			STATUS	current
			::= { hmWanMbus8F 101 }

hmWanMbus90			OBJECT IDENTIFIER ::= { hmWanMbus 144 }

hmWanMbus90IdNumber		OBJECT-TYPE
			SYNTAX	Gauge32
			MAX-ACCESS	read-only
			STATUS	current
			::= { hmWanMbus90 1 }

hmWanMbus90Manufacturer	OBJECT-TYPE
			SYNTAX	Gauge32
			MAX-ACCESS	read-only
			STATUS	current
			::= { hmWanMbus90 2 }

hmWanMbus90Version		OBJECT-TYPE
			SYNTAX	Gauge32
			MAX-ACCESS	read-only
			STATUS	current
			::= { hmWanMbus90 3 }

hmWanMbus90Medium		OBJECT-TYPE
			SYNTAX	Gauge32
			MAX-ACCESS	read-only
			STATUS	current
			::= { hmWanMbus90 4 }

hmWanMbus90Status		OBJECT-TYPE
			SYNTAX	Gauge32
			MAX-ACCESS	read-only
			STATUS	current
			::= { hmWanMbus90 5 }

hmWanMbus90VIF00		OBJECT-TYPE
			SYNTAX	INTEGER
			MAX-ACCESS	read-only
			STATUS	current
			::= { hmWanMbus90 6 }

hmWanMbus90Value00		OBJECT-TYPE
			SYNTAX	INTEGER
			MAX-ACCESS	read-only
			STATUS	current
			::= { hmWanMbus90 7 }

hmWanMbus90VIF01		OBJECT-TYPE
			SYNTAX	INTEGER
			MAX-ACCESS	read-only
			STATUS	current
			::= { hmWanMbus90 8 }

hmWanMbus90Value01		OBJECT-TYPE
			SYNTAX	INTEGER
			MAX-ACCESS	read-only
			STATUS	current
			::= { hmWanMbus90 9 }

hmWanMbus90VIF02		OBJECT-TYPE
			SYNTAX	INTEGER
			MAX-ACCESS	read-only
			STATUS	current
			::= { hmWanMbus90 10 }

hmWanMbus90Value02		OBJECT-TYPE
			SYNTAX	INTEGER
			MAX-ACCESS	read-only
			STATUS	current
			::= { hmWanMbus90 11 }

hmWanMbus90VIF03		OBJECT-TYPE
			SYNTAX	INTEGER
			MAX-ACCESS	read-only
			STATUS	current
			::= { hmWanMbus90 12 }

hmWanMbus90Value03		OBJECT-TYPE
			SYNTAX	INTEGER
			MAX-ACCESS	read-only
			STATUS	current
			::= { hmWanMbus90 13 }

hmWanMbus90VIF04		OBJECT-TYPE
			SYNTAX	INTEGER
			MAX-ACCESS	read-only
			STATUS	current
			::= { hmWanMbus90 14 }

hmWanMbus90Value04		OBJECT-TYPE
			SYNTAX	INTEGER
			MAX-ACCESS	read-only
			STATUS	current
			::= { hmWanMbus90 15 }

hmWanMbus90VIF05		OBJECT-TYPE
			SYNTAX	INTEGER
			MAX-ACCESS	read-only
			STATUS	current
			::= { hmWanMbus90 16 }

hmWanMbus90Value05		OBJECT-TYPE
			SYNTAX	INTEGER
			MAX-ACCESS	read-only
			STATUS	current
			::= { hmWanMbus90 17 }

hmWanMbus90VIF06		OBJECT-TYPE
			SYNTAX	INTEGER
			MAX-ACCESS	read-only
			STATUS	current
			::= { hmWanMbus90 18 }

hmWanMbus90Value06		OBJECT-TYPE
			SYNTAX	INTEGER
			MAX-ACCESS	read-only
			STATUS	current
			::= { hmWanMbus90 19 }

hmWanMbus90VIF07		OBJECT-TYPE
			SYNTAX	INTEGER
			MAX-ACCESS	read-only
			STATUS	current
			::= { hmWanMbus90 20 }

hmWanMbus90Value07		OBJECT-TYPE
			SYNTAX	INTEGER
			MAX-ACCESS	read-only
			STATUS	current
			::= { hmWanMbus90 21 }

hmWanMbus90VIF08		OBJECT-TYPE
			SYNTAX	INTEGER
			MAX-ACCESS	read-only
			STATUS	current
			::= { hmWanMbus90 22 }

hmWanMbus90Value08		OBJECT-TYPE
			SYNTAX	INTEGER
			MAX-ACCESS	read-only
			STATUS	current
			::= { hmWanMbus90 23 }

hmWanMbus90VIF09		OBJECT-TYPE
			SYNTAX	INTEGER
			MAX-ACCESS	read-only
			STATUS	current
			::= { hmWanMbus90 24 }

hmWanMbus90Value09		OBJECT-TYPE
			SYNTAX	INTEGER
			MAX-ACCESS	read-only
			STATUS	current
			::= { hmWanMbus90 25 }

hmWanMbus90VIF0A		OBJECT-TYPE
			SYNTAX	INTEGER
			MAX-ACCESS	read-only
			STATUS	current
			::= { hmWanMbus90 26 }

hmWanMbus90Value0A		OBJECT-TYPE
			SYNTAX	INTEGER
			MAX-ACCESS	read-only
			STATUS	current
			::= { hmWanMbus90 27 }

hmWanMbus90VIF0B		OBJECT-TYPE
			SYNTAX	INTEGER
			MAX-ACCESS	read-only
			STATUS	current
			::= { hmWanMbus90 28 }

hmWanMbus90Value0B		OBJECT-TYPE
			SYNTAX	INTEGER
			MAX-ACCESS	read-only
			STATUS	current
			::= { hmWanMbus90 29 }

hmWanMbus90VIF0C		OBJECT-TYPE
			SYNTAX	INTEGER
			MAX-ACCESS	read-only
			STATUS	current
			::= { hmWanMbus90 30 }

hmWanMbus90Value0C		OBJECT-TYPE
			SYNTAX	INTEGER
			MAX-ACCESS	read-only
			STATUS	current
			::= { hmWanMbus90 31 }

hmWanMbus90VIF0D		OBJECT-TYPE
			SYNTAX	INTEGER
			MAX-ACCESS	read-only
			STATUS	current
			::= { hmWanMbus90 32 }

hmWanMbus90Value0D		OBJECT-TYPE
			SYNTAX	INTEGER
			MAX-ACCESS	read-only
			STATUS	current
			::= { hmWanMbus90 33 }

hmWanMbus90VIF0E		OBJECT-TYPE
			SYNTAX	INTEGER
			MAX-ACCESS	read-only
			STATUS	current
			::= { hmWanMbus90 34 }

hmWanMbus90Value0E		OBJECT-TYPE
			SYNTAX	INTEGER
			MAX-ACCESS	read-only
			STATUS	current
			::= { hmWanMbus90 35 }

hmWanMbus90VIF0F		OBJECT-TYPE
			SYNTAX	INTEGER
			MAX-ACCESS	read-only
			STATUS	current
			::= { hmWanMbus90 36 }

hmWanMbus90Value0F		OBJECT-TYPE
			SYNTAX	INTEGER
			MAX-ACCESS	read-only
			STATUS	current
			::= { hmWanMbus90 37 }

hmWanMbus90VIF10		OBJECT-TYPE
			SYNTAX	INTEGER
			MAX-ACCESS	read-only
			STATUS	current
			::= { hmWanMbus90 38 }

hmWanMbus90Value10		OBJECT-TYPE
			SYNTAX	INTEGER
			MAX-ACCESS	read-only
			STATUS	current
			::= { hmWanMbus90 39 }

hmWanMbus90VIF11		OBJECT-TYPE
			SYNTAX	INTEGER
			MAX-ACCESS	read-only
			STATUS	current
			::= { hmWanMbus90 40 }

hmWanMbus90Value11		OBJECT-TYPE
			SYNTAX	INTEGER
			MAX-ACCESS	read-only
			STATUS	current
			::= { hmWanMbus90 41 }

hmWanMbus90VIF12		OBJECT-TYPE
			SYNTAX	INTEGER
			MAX-ACCESS	read-only
			STATUS	current
			::= { hmWanMbus90 42 }

hmWanMbus90Value12		OBJECT-TYPE
			SYNTAX	INTEGER
			MAX-ACCESS	read-only
			STATUS	current
			::= { hmWanMbus90 43 }

hmWanMbus90VIF13		OBJECT-TYPE
			SYNTAX	INTEGER
			MAX-ACCESS	read-only
			STATUS	current
			::= { hmWanMbus90 44 }

hmWanMbus90Value13		OBJECT-TYPE
			SYNTAX	INTEGER
			MAX-ACCESS	read-only
			STATUS	current
			::= { hmWanMbus90 45 }

hmWanMbus90VIF14		OBJECT-TYPE
			SYNTAX	INTEGER
			MAX-ACCESS	read-only
			STATUS	current
			::= { hmWanMbus90 46 }

hmWanMbus90Value14		OBJECT-TYPE
			SYNTAX	INTEGER
			MAX-ACCESS	read-only
			STATUS	current
			::= { hmWanMbus90 47 }

hmWanMbus90VIF15		OBJECT-TYPE
			SYNTAX	INTEGER
			MAX-ACCESS	read-only
			STATUS	current
			::= { hmWanMbus90 48 }

hmWanMbus90Value15		OBJECT-TYPE
			SYNTAX	INTEGER
			MAX-ACCESS	read-only
			STATUS	current
			::= { hmWanMbus90 49 }

hmWanMbus90VIF16		OBJECT-TYPE
			SYNTAX	INTEGER
			MAX-ACCESS	read-only
			STATUS	current
			::= { hmWanMbus90 50 }

hmWanMbus90Value16		OBJECT-TYPE
			SYNTAX	INTEGER
			MAX-ACCESS	read-only
			STATUS	current
			::= { hmWanMbus90 51 }

hmWanMbus90VIF17		OBJECT-TYPE
			SYNTAX	INTEGER
			MAX-ACCESS	read-only
			STATUS	current
			::= { hmWanMbus90 52 }

hmWanMbus90Value17		OBJECT-TYPE
			SYNTAX	INTEGER
			MAX-ACCESS	read-only
			STATUS	current
			::= { hmWanMbus90 53 }

hmWanMbus90VIF18		OBJECT-TYPE
			SYNTAX	INTEGER
			MAX-ACCESS	read-only
			STATUS	current
			::= { hmWanMbus90 54 }

hmWanMbus90Value18		OBJECT-TYPE
			SYNTAX	INTEGER
			MAX-ACCESS	read-only
			STATUS	current
			::= { hmWanMbus90 55 }

hmWanMbus90VIF19		OBJECT-TYPE
			SYNTAX	INTEGER
			MAX-ACCESS	read-only
			STATUS	current
			::= { hmWanMbus90 56 }

hmWanMbus90Value19		OBJECT-TYPE
			SYNTAX	INTEGER
			MAX-ACCESS	read-only
			STATUS	current
			::= { hmWanMbus90 57 }

hmWanMbus90VIF1A		OBJECT-TYPE
			SYNTAX	INTEGER
			MAX-ACCESS	read-only
			STATUS	current
			::= { hmWanMbus90 58 }

hmWanMbus90Value1A		OBJECT-TYPE
			SYNTAX	INTEGER
			MAX-ACCESS	read-only
			STATUS	current
			::= { hmWanMbus90 59 }

hmWanMbus90VIF1B		OBJECT-TYPE
			SYNTAX	INTEGER
			MAX-ACCESS	read-only
			STATUS	current
			::= { hmWanMbus90 60 }

hmWanMbus90Value1B		OBJECT-TYPE
			SYNTAX	INTEGER
			MAX-ACCESS	read-only
			STATUS	current
			::= { hmWanMbus90 61 }

hmWanMbus90VIF1C		OBJECT-TYPE
			SYNTAX	INTEGER
			MAX-ACCESS	read-only
			STATUS	current
			::= { hmWanMbus90 62 }

hmWanMbus90Value1C		OBJECT-TYPE
			SYNTAX	INTEGER
			MAX-ACCESS	read-only
			STATUS	current
			::= { hmWanMbus90 63 }

hmWanMbus90VIF1D		OBJECT-TYPE
			SYNTAX	INTEGER
			MAX-ACCESS	read-only
			STATUS	current
			::= { hmWanMbus90 64 }

hmWanMbus90Value1D		OBJECT-TYPE
			SYNTAX	INTEGER
			MAX-ACCESS	read-only
			STATUS	current
			::= { hmWanMbus90 65 }

hmWanMbus90VIF1E		OBJECT-TYPE
			SYNTAX	INTEGER
			MAX-ACCESS	read-only
			STATUS	current
			::= { hmWanMbus90 66 }

hmWanMbus90Value1E		OBJECT-TYPE
			SYNTAX	INTEGER
			MAX-ACCESS	read-only
			STATUS	current
			::= { hmWanMbus90 67 }

hmWanMbus90VIF1F		OBJECT-TYPE
			SYNTAX	INTEGER
			MAX-ACCESS	read-only
			STATUS	current
			::= { hmWanMbus90 68 }

hmWanMbus90Value1F		OBJECT-TYPE
			SYNTAX	INTEGER
			MAX-ACCESS	read-only
			STATUS	current
			::= { hmWanMbus90 69 }

hmWanMbus90VIF20		OBJECT-TYPE
			SYNTAX	INTEGER
			MAX-ACCESS	read-only
			STATUS	current
			::= { hmWanMbus90 70 }

hmWanMbus90Value20		OBJECT-TYPE
			SYNTAX	INTEGER
			MAX-ACCESS	read-only
			STATUS	current
			::= { hmWanMbus90 71 }

hmWanMbus90VIF21		OBJECT-TYPE
			SYNTAX	INTEGER
			MAX-ACCESS	read-only
			STATUS	current
			::= { hmWanMbus90 72 }

hmWanMbus90Value21		OBJECT-TYPE
			SYNTAX	INTEGER
			MAX-ACCESS	read-only
			STATUS	current
			::= { hmWanMbus90 73 }

hmWanMbus90VIF22		OBJECT-TYPE
			SYNTAX	INTEGER
			MAX-ACCESS	read-only
			STATUS	current
			::= { hmWanMbus90 74 }

hmWanMbus90Value22		OBJECT-TYPE
			SYNTAX	INTEGER
			MAX-ACCESS	read-only
			STATUS	current
			::= { hmWanMbus90 75 }

hmWanMbus90VIF23		OBJECT-TYPE
			SYNTAX	INTEGER
			MAX-ACCESS	read-only
			STATUS	current
			::= { hmWanMbus90 76 }

hmWanMbus90Value23		OBJECT-TYPE
			SYNTAX	INTEGER
			MAX-ACCESS	read-only
			STATUS	current
			::= { hmWanMbus90 77 }

hmWanMbus90VIF24		OBJECT-TYPE
			SYNTAX	INTEGER
			MAX-ACCESS	read-only
			STATUS	current
			::= { hmWanMbus90 78 }

hmWanMbus90Value24		OBJECT-TYPE
			SYNTAX	INTEGER
			MAX-ACCESS	read-only
			STATUS	current
			::= { hmWanMbus90 79 }

hmWanMbus90VIF25		OBJECT-TYPE
			SYNTAX	INTEGER
			MAX-ACCESS	read-only
			STATUS	current
			::= { hmWanMbus90 80 }

hmWanMbus90Value25		OBJECT-TYPE
			SYNTAX	INTEGER
			MAX-ACCESS	read-only
			STATUS	current
			::= { hmWanMbus90 81 }

hmWanMbus90VIF26		OBJECT-TYPE
			SYNTAX	INTEGER
			MAX-ACCESS	read-only
			STATUS	current
			::= { hmWanMbus90 82 }

hmWanMbus90Value26		OBJECT-TYPE
			SYNTAX	INTEGER
			MAX-ACCESS	read-only
			STATUS	current
			::= { hmWanMbus90 83 }

hmWanMbus90VIF27		OBJECT-TYPE
			SYNTAX	INTEGER
			MAX-ACCESS	read-only
			STATUS	current
			::= { hmWanMbus90 84 }

hmWanMbus90Value27		OBJECT-TYPE
			SYNTAX	INTEGER
			MAX-ACCESS	read-only
			STATUS	current
			::= { hmWanMbus90 85 }

hmWanMbus90VIF28		OBJECT-TYPE
			SYNTAX	INTEGER
			MAX-ACCESS	read-only
			STATUS	current
			::= { hmWanMbus90 86 }

hmWanMbus90Value28		OBJECT-TYPE
			SYNTAX	INTEGER
			MAX-ACCESS	read-only
			STATUS	current
			::= { hmWanMbus90 87 }

hmWanMbus90VIF29		OBJECT-TYPE
			SYNTAX	INTEGER
			MAX-ACCESS	read-only
			STATUS	current
			::= { hmWanMbus90 88 }

hmWanMbus90Value29		OBJECT-TYPE
			SYNTAX	INTEGER
			MAX-ACCESS	read-only
			STATUS	current
			::= { hmWanMbus90 89 }

hmWanMbus90VIF2A		OBJECT-TYPE
			SYNTAX	INTEGER
			MAX-ACCESS	read-only
			STATUS	current
			::= { hmWanMbus90 90 }

hmWanMbus90Value2A		OBJECT-TYPE
			SYNTAX	INTEGER
			MAX-ACCESS	read-only
			STATUS	current
			::= { hmWanMbus90 91 }

hmWanMbus90VIF2B		OBJECT-TYPE
			SYNTAX	INTEGER
			MAX-ACCESS	read-only
			STATUS	current
			::= { hmWanMbus90 92 }

hmWanMbus90Value2B		OBJECT-TYPE
			SYNTAX	INTEGER
			MAX-ACCESS	read-only
			STATUS	current
			::= { hmWanMbus90 93 }

hmWanMbus90VIF2C		OBJECT-TYPE
			SYNTAX	INTEGER
			MAX-ACCESS	read-only
			STATUS	current
			::= { hmWanMbus90 94 }

hmWanMbus90Value2C		OBJECT-TYPE
			SYNTAX	INTEGER
			MAX-ACCESS	read-only
			STATUS	current
			::= { hmWanMbus90 95 }

hmWanMbus90VIF2D		OBJECT-TYPE
			SYNTAX	INTEGER
			MAX-ACCESS	read-only
			STATUS	current
			::= { hmWanMbus90 96 }

hmWanMbus90Value2D		OBJECT-TYPE
			SYNTAX	INTEGER
			MAX-ACCESS	read-only
			STATUS	current
			::= { hmWanMbus90 97 }

hmWanMbus90VIF2E		OBJECT-TYPE
			SYNTAX	INTEGER
			MAX-ACCESS	read-only
			STATUS	current
			::= { hmWanMbus90 98 }

hmWanMbus90Value2E		OBJECT-TYPE
			SYNTAX	INTEGER
			MAX-ACCESS	read-only
			STATUS	current
			::= { hmWanMbus90 99 }

hmWanMbus90VIF2F		OBJECT-TYPE
			SYNTAX	INTEGER
			MAX-ACCESS	read-only
			STATUS	current
			::= { hmWanMbus90 100 }

hmWanMbus90Value2F		OBJECT-TYPE
			SYNTAX	INTEGER
			MAX-ACCESS	read-only
			STATUS	current
			::= { hmWanMbus90 101 }

hmWanMbus91			OBJECT IDENTIFIER ::= { hmWanMbus 145 }

hmWanMbus91IdNumber		OBJECT-TYPE
			SYNTAX	Gauge32
			MAX-ACCESS	read-only
			STATUS	current
			::= { hmWanMbus91 1 }

hmWanMbus91Manufacturer	OBJECT-TYPE
			SYNTAX	Gauge32
			MAX-ACCESS	read-only
			STATUS	current
			::= { hmWanMbus91 2 }

hmWanMbus91Version		OBJECT-TYPE
			SYNTAX	Gauge32
			MAX-ACCESS	read-only
			STATUS	current
			::= { hmWanMbus91 3 }

hmWanMbus91Medium		OBJECT-TYPE
			SYNTAX	Gauge32
			MAX-ACCESS	read-only
			STATUS	current
			::= { hmWanMbus91 4 }

hmWanMbus91Status		OBJECT-TYPE
			SYNTAX	Gauge32
			MAX-ACCESS	read-only
			STATUS	current
			::= { hmWanMbus91 5 }

hmWanMbus91VIF00		OBJECT-TYPE
			SYNTAX	INTEGER
			MAX-ACCESS	read-only
			STATUS	current
			::= { hmWanMbus91 6 }

hmWanMbus91Value00		OBJECT-TYPE
			SYNTAX	INTEGER
			MAX-ACCESS	read-only
			STATUS	current
			::= { hmWanMbus91 7 }

hmWanMbus91VIF01		OBJECT-TYPE
			SYNTAX	INTEGER
			MAX-ACCESS	read-only
			STATUS	current
			::= { hmWanMbus91 8 }

hmWanMbus91Value01		OBJECT-TYPE
			SYNTAX	INTEGER
			MAX-ACCESS	read-only
			STATUS	current
			::= { hmWanMbus91 9 }

hmWanMbus91VIF02		OBJECT-TYPE
			SYNTAX	INTEGER
			MAX-ACCESS	read-only
			STATUS	current
			::= { hmWanMbus91 10 }

hmWanMbus91Value02		OBJECT-TYPE
			SYNTAX	INTEGER
			MAX-ACCESS	read-only
			STATUS	current
			::= { hmWanMbus91 11 }

hmWanMbus91VIF03		OBJECT-TYPE
			SYNTAX	INTEGER
			MAX-ACCESS	read-only
			STATUS	current
			::= { hmWanMbus91 12 }

hmWanMbus91Value03		OBJECT-TYPE
			SYNTAX	INTEGER
			MAX-ACCESS	read-only
			STATUS	current
			::= { hmWanMbus91 13 }

hmWanMbus91VIF04		OBJECT-TYPE
			SYNTAX	INTEGER
			MAX-ACCESS	read-only
			STATUS	current
			::= { hmWanMbus91 14 }

hmWanMbus91Value04		OBJECT-TYPE
			SYNTAX	INTEGER
			MAX-ACCESS	read-only
			STATUS	current
			::= { hmWanMbus91 15 }

hmWanMbus91VIF05		OBJECT-TYPE
			SYNTAX	INTEGER
			MAX-ACCESS	read-only
			STATUS	current
			::= { hmWanMbus91 16 }

hmWanMbus91Value05		OBJECT-TYPE
			SYNTAX	INTEGER
			MAX-ACCESS	read-only
			STATUS	current
			::= { hmWanMbus91 17 }

hmWanMbus91VIF06		OBJECT-TYPE
			SYNTAX	INTEGER
			MAX-ACCESS	read-only
			STATUS	current
			::= { hmWanMbus91 18 }

hmWanMbus91Value06		OBJECT-TYPE
			SYNTAX	INTEGER
			MAX-ACCESS	read-only
			STATUS	current
			::= { hmWanMbus91 19 }

hmWanMbus91VIF07		OBJECT-TYPE
			SYNTAX	INTEGER
			MAX-ACCESS	read-only
			STATUS	current
			::= { hmWanMbus91 20 }

hmWanMbus91Value07		OBJECT-TYPE
			SYNTAX	INTEGER
			MAX-ACCESS	read-only
			STATUS	current
			::= { hmWanMbus91 21 }

hmWanMbus91VIF08		OBJECT-TYPE
			SYNTAX	INTEGER
			MAX-ACCESS	read-only
			STATUS	current
			::= { hmWanMbus91 22 }

hmWanMbus91Value08		OBJECT-TYPE
			SYNTAX	INTEGER
			MAX-ACCESS	read-only
			STATUS	current
			::= { hmWanMbus91 23 }

hmWanMbus91VIF09		OBJECT-TYPE
			SYNTAX	INTEGER
			MAX-ACCESS	read-only
			STATUS	current
			::= { hmWanMbus91 24 }

hmWanMbus91Value09		OBJECT-TYPE
			SYNTAX	INTEGER
			MAX-ACCESS	read-only
			STATUS	current
			::= { hmWanMbus91 25 }

hmWanMbus91VIF0A		OBJECT-TYPE
			SYNTAX	INTEGER
			MAX-ACCESS	read-only
			STATUS	current
			::= { hmWanMbus91 26 }

hmWanMbus91Value0A		OBJECT-TYPE
			SYNTAX	INTEGER
			MAX-ACCESS	read-only
			STATUS	current
			::= { hmWanMbus91 27 }

hmWanMbus91VIF0B		OBJECT-TYPE
			SYNTAX	INTEGER
			MAX-ACCESS	read-only
			STATUS	current
			::= { hmWanMbus91 28 }

hmWanMbus91Value0B		OBJECT-TYPE
			SYNTAX	INTEGER
			MAX-ACCESS	read-only
			STATUS	current
			::= { hmWanMbus91 29 }

hmWanMbus91VIF0C		OBJECT-TYPE
			SYNTAX	INTEGER
			MAX-ACCESS	read-only
			STATUS	current
			::= { hmWanMbus91 30 }

hmWanMbus91Value0C		OBJECT-TYPE
			SYNTAX	INTEGER
			MAX-ACCESS	read-only
			STATUS	current
			::= { hmWanMbus91 31 }

hmWanMbus91VIF0D		OBJECT-TYPE
			SYNTAX	INTEGER
			MAX-ACCESS	read-only
			STATUS	current
			::= { hmWanMbus91 32 }

hmWanMbus91Value0D		OBJECT-TYPE
			SYNTAX	INTEGER
			MAX-ACCESS	read-only
			STATUS	current
			::= { hmWanMbus91 33 }

hmWanMbus91VIF0E		OBJECT-TYPE
			SYNTAX	INTEGER
			MAX-ACCESS	read-only
			STATUS	current
			::= { hmWanMbus91 34 }

hmWanMbus91Value0E		OBJECT-TYPE
			SYNTAX	INTEGER
			MAX-ACCESS	read-only
			STATUS	current
			::= { hmWanMbus91 35 }

hmWanMbus91VIF0F		OBJECT-TYPE
			SYNTAX	INTEGER
			MAX-ACCESS	read-only
			STATUS	current
			::= { hmWanMbus91 36 }

hmWanMbus91Value0F		OBJECT-TYPE
			SYNTAX	INTEGER
			MAX-ACCESS	read-only
			STATUS	current
			::= { hmWanMbus91 37 }

hmWanMbus91VIF10		OBJECT-TYPE
			SYNTAX	INTEGER
			MAX-ACCESS	read-only
			STATUS	current
			::= { hmWanMbus91 38 }

hmWanMbus91Value10		OBJECT-TYPE
			SYNTAX	INTEGER
			MAX-ACCESS	read-only
			STATUS	current
			::= { hmWanMbus91 39 }

hmWanMbus91VIF11		OBJECT-TYPE
			SYNTAX	INTEGER
			MAX-ACCESS	read-only
			STATUS	current
			::= { hmWanMbus91 40 }

hmWanMbus91Value11		OBJECT-TYPE
			SYNTAX	INTEGER
			MAX-ACCESS	read-only
			STATUS	current
			::= { hmWanMbus91 41 }

hmWanMbus91VIF12		OBJECT-TYPE
			SYNTAX	INTEGER
			MAX-ACCESS	read-only
			STATUS	current
			::= { hmWanMbus91 42 }

hmWanMbus91Value12		OBJECT-TYPE
			SYNTAX	INTEGER
			MAX-ACCESS	read-only
			STATUS	current
			::= { hmWanMbus91 43 }

hmWanMbus91VIF13		OBJECT-TYPE
			SYNTAX	INTEGER
			MAX-ACCESS	read-only
			STATUS	current
			::= { hmWanMbus91 44 }

hmWanMbus91Value13		OBJECT-TYPE
			SYNTAX	INTEGER
			MAX-ACCESS	read-only
			STATUS	current
			::= { hmWanMbus91 45 }

hmWanMbus91VIF14		OBJECT-TYPE
			SYNTAX	INTEGER
			MAX-ACCESS	read-only
			STATUS	current
			::= { hmWanMbus91 46 }

hmWanMbus91Value14		OBJECT-TYPE
			SYNTAX	INTEGER
			MAX-ACCESS	read-only
			STATUS	current
			::= { hmWanMbus91 47 }

hmWanMbus91VIF15		OBJECT-TYPE
			SYNTAX	INTEGER
			MAX-ACCESS	read-only
			STATUS	current
			::= { hmWanMbus91 48 }

hmWanMbus91Value15		OBJECT-TYPE
			SYNTAX	INTEGER
			MAX-ACCESS	read-only
			STATUS	current
			::= { hmWanMbus91 49 }

hmWanMbus91VIF16		OBJECT-TYPE
			SYNTAX	INTEGER
			MAX-ACCESS	read-only
			STATUS	current
			::= { hmWanMbus91 50 }

hmWanMbus91Value16		OBJECT-TYPE
			SYNTAX	INTEGER
			MAX-ACCESS	read-only
			STATUS	current
			::= { hmWanMbus91 51 }

hmWanMbus91VIF17		OBJECT-TYPE
			SYNTAX	INTEGER
			MAX-ACCESS	read-only
			STATUS	current
			::= { hmWanMbus91 52 }

hmWanMbus91Value17		OBJECT-TYPE
			SYNTAX	INTEGER
			MAX-ACCESS	read-only
			STATUS	current
			::= { hmWanMbus91 53 }

hmWanMbus91VIF18		OBJECT-TYPE
			SYNTAX	INTEGER
			MAX-ACCESS	read-only
			STATUS	current
			::= { hmWanMbus91 54 }

hmWanMbus91Value18		OBJECT-TYPE
			SYNTAX	INTEGER
			MAX-ACCESS	read-only
			STATUS	current
			::= { hmWanMbus91 55 }

hmWanMbus91VIF19		OBJECT-TYPE
			SYNTAX	INTEGER
			MAX-ACCESS	read-only
			STATUS	current
			::= { hmWanMbus91 56 }

hmWanMbus91Value19		OBJECT-TYPE
			SYNTAX	INTEGER
			MAX-ACCESS	read-only
			STATUS	current
			::= { hmWanMbus91 57 }

hmWanMbus91VIF1A		OBJECT-TYPE
			SYNTAX	INTEGER
			MAX-ACCESS	read-only
			STATUS	current
			::= { hmWanMbus91 58 }

hmWanMbus91Value1A		OBJECT-TYPE
			SYNTAX	INTEGER
			MAX-ACCESS	read-only
			STATUS	current
			::= { hmWanMbus91 59 }

hmWanMbus91VIF1B		OBJECT-TYPE
			SYNTAX	INTEGER
			MAX-ACCESS	read-only
			STATUS	current
			::= { hmWanMbus91 60 }

hmWanMbus91Value1B		OBJECT-TYPE
			SYNTAX	INTEGER
			MAX-ACCESS	read-only
			STATUS	current
			::= { hmWanMbus91 61 }

hmWanMbus91VIF1C		OBJECT-TYPE
			SYNTAX	INTEGER
			MAX-ACCESS	read-only
			STATUS	current
			::= { hmWanMbus91 62 }

hmWanMbus91Value1C		OBJECT-TYPE
			SYNTAX	INTEGER
			MAX-ACCESS	read-only
			STATUS	current
			::= { hmWanMbus91 63 }

hmWanMbus91VIF1D		OBJECT-TYPE
			SYNTAX	INTEGER
			MAX-ACCESS	read-only
			STATUS	current
			::= { hmWanMbus91 64 }

hmWanMbus91Value1D		OBJECT-TYPE
			SYNTAX	INTEGER
			MAX-ACCESS	read-only
			STATUS	current
			::= { hmWanMbus91 65 }

hmWanMbus91VIF1E		OBJECT-TYPE
			SYNTAX	INTEGER
			MAX-ACCESS	read-only
			STATUS	current
			::= { hmWanMbus91 66 }

hmWanMbus91Value1E		OBJECT-TYPE
			SYNTAX	INTEGER
			MAX-ACCESS	read-only
			STATUS	current
			::= { hmWanMbus91 67 }

hmWanMbus91VIF1F		OBJECT-TYPE
			SYNTAX	INTEGER
			MAX-ACCESS	read-only
			STATUS	current
			::= { hmWanMbus91 68 }

hmWanMbus91Value1F		OBJECT-TYPE
			SYNTAX	INTEGER
			MAX-ACCESS	read-only
			STATUS	current
			::= { hmWanMbus91 69 }

hmWanMbus91VIF20		OBJECT-TYPE
			SYNTAX	INTEGER
			MAX-ACCESS	read-only
			STATUS	current
			::= { hmWanMbus91 70 }

hmWanMbus91Value20		OBJECT-TYPE
			SYNTAX	INTEGER
			MAX-ACCESS	read-only
			STATUS	current
			::= { hmWanMbus91 71 }

hmWanMbus91VIF21		OBJECT-TYPE
			SYNTAX	INTEGER
			MAX-ACCESS	read-only
			STATUS	current
			::= { hmWanMbus91 72 }

hmWanMbus91Value21		OBJECT-TYPE
			SYNTAX	INTEGER
			MAX-ACCESS	read-only
			STATUS	current
			::= { hmWanMbus91 73 }

hmWanMbus91VIF22		OBJECT-TYPE
			SYNTAX	INTEGER
			MAX-ACCESS	read-only
			STATUS	current
			::= { hmWanMbus91 74 }

hmWanMbus91Value22		OBJECT-TYPE
			SYNTAX	INTEGER
			MAX-ACCESS	read-only
			STATUS	current
			::= { hmWanMbus91 75 }

hmWanMbus91VIF23		OBJECT-TYPE
			SYNTAX	INTEGER
			MAX-ACCESS	read-only
			STATUS	current
			::= { hmWanMbus91 76 }

hmWanMbus91Value23		OBJECT-TYPE
			SYNTAX	INTEGER
			MAX-ACCESS	read-only
			STATUS	current
			::= { hmWanMbus91 77 }

hmWanMbus91VIF24		OBJECT-TYPE
			SYNTAX	INTEGER
			MAX-ACCESS	read-only
			STATUS	current
			::= { hmWanMbus91 78 }

hmWanMbus91Value24		OBJECT-TYPE
			SYNTAX	INTEGER
			MAX-ACCESS	read-only
			STATUS	current
			::= { hmWanMbus91 79 }

hmWanMbus91VIF25		OBJECT-TYPE
			SYNTAX	INTEGER
			MAX-ACCESS	read-only
			STATUS	current
			::= { hmWanMbus91 80 }

hmWanMbus91Value25		OBJECT-TYPE
			SYNTAX	INTEGER
			MAX-ACCESS	read-only
			STATUS	current
			::= { hmWanMbus91 81 }

hmWanMbus91VIF26		OBJECT-TYPE
			SYNTAX	INTEGER
			MAX-ACCESS	read-only
			STATUS	current
			::= { hmWanMbus91 82 }

hmWanMbus91Value26		OBJECT-TYPE
			SYNTAX	INTEGER
			MAX-ACCESS	read-only
			STATUS	current
			::= { hmWanMbus91 83 }

hmWanMbus91VIF27		OBJECT-TYPE
			SYNTAX	INTEGER
			MAX-ACCESS	read-only
			STATUS	current
			::= { hmWanMbus91 84 }

hmWanMbus91Value27		OBJECT-TYPE
			SYNTAX	INTEGER
			MAX-ACCESS	read-only
			STATUS	current
			::= { hmWanMbus91 85 }

hmWanMbus91VIF28		OBJECT-TYPE
			SYNTAX	INTEGER
			MAX-ACCESS	read-only
			STATUS	current
			::= { hmWanMbus91 86 }

hmWanMbus91Value28		OBJECT-TYPE
			SYNTAX	INTEGER
			MAX-ACCESS	read-only
			STATUS	current
			::= { hmWanMbus91 87 }

hmWanMbus91VIF29		OBJECT-TYPE
			SYNTAX	INTEGER
			MAX-ACCESS	read-only
			STATUS	current
			::= { hmWanMbus91 88 }

hmWanMbus91Value29		OBJECT-TYPE
			SYNTAX	INTEGER
			MAX-ACCESS	read-only
			STATUS	current
			::= { hmWanMbus91 89 }

hmWanMbus91VIF2A		OBJECT-TYPE
			SYNTAX	INTEGER
			MAX-ACCESS	read-only
			STATUS	current
			::= { hmWanMbus91 90 }

hmWanMbus91Value2A		OBJECT-TYPE
			SYNTAX	INTEGER
			MAX-ACCESS	read-only
			STATUS	current
			::= { hmWanMbus91 91 }

hmWanMbus91VIF2B		OBJECT-TYPE
			SYNTAX	INTEGER
			MAX-ACCESS	read-only
			STATUS	current
			::= { hmWanMbus91 92 }

hmWanMbus91Value2B		OBJECT-TYPE
			SYNTAX	INTEGER
			MAX-ACCESS	read-only
			STATUS	current
			::= { hmWanMbus91 93 }

hmWanMbus91VIF2C		OBJECT-TYPE
			SYNTAX	INTEGER
			MAX-ACCESS	read-only
			STATUS	current
			::= { hmWanMbus91 94 }

hmWanMbus91Value2C		OBJECT-TYPE
			SYNTAX	INTEGER
			MAX-ACCESS	read-only
			STATUS	current
			::= { hmWanMbus91 95 }

hmWanMbus91VIF2D		OBJECT-TYPE
			SYNTAX	INTEGER
			MAX-ACCESS	read-only
			STATUS	current
			::= { hmWanMbus91 96 }

hmWanMbus91Value2D		OBJECT-TYPE
			SYNTAX	INTEGER
			MAX-ACCESS	read-only
			STATUS	current
			::= { hmWanMbus91 97 }

hmWanMbus91VIF2E		OBJECT-TYPE
			SYNTAX	INTEGER
			MAX-ACCESS	read-only
			STATUS	current
			::= { hmWanMbus91 98 }

hmWanMbus91Value2E		OBJECT-TYPE
			SYNTAX	INTEGER
			MAX-ACCESS	read-only
			STATUS	current
			::= { hmWanMbus91 99 }

hmWanMbus91VIF2F		OBJECT-TYPE
			SYNTAX	INTEGER
			MAX-ACCESS	read-only
			STATUS	current
			::= { hmWanMbus91 100 }

hmWanMbus91Value2F		OBJECT-TYPE
			SYNTAX	INTEGER
			MAX-ACCESS	read-only
			STATUS	current
			::= { hmWanMbus91 101 }

hmWanMbus92			OBJECT IDENTIFIER ::= { hmWanMbus 146 }

hmWanMbus92IdNumber		OBJECT-TYPE
			SYNTAX	Gauge32
			MAX-ACCESS	read-only
			STATUS	current
			::= { hmWanMbus92 1 }

hmWanMbus92Manufacturer	OBJECT-TYPE
			SYNTAX	Gauge32
			MAX-ACCESS	read-only
			STATUS	current
			::= { hmWanMbus92 2 }

hmWanMbus92Version		OBJECT-TYPE
			SYNTAX	Gauge32
			MAX-ACCESS	read-only
			STATUS	current
			::= { hmWanMbus92 3 }

hmWanMbus92Medium		OBJECT-TYPE
			SYNTAX	Gauge32
			MAX-ACCESS	read-only
			STATUS	current
			::= { hmWanMbus92 4 }

hmWanMbus92Status		OBJECT-TYPE
			SYNTAX	Gauge32
			MAX-ACCESS	read-only
			STATUS	current
			::= { hmWanMbus92 5 }

hmWanMbus92VIF00		OBJECT-TYPE
			SYNTAX	INTEGER
			MAX-ACCESS	read-only
			STATUS	current
			::= { hmWanMbus92 6 }

hmWanMbus92Value00		OBJECT-TYPE
			SYNTAX	INTEGER
			MAX-ACCESS	read-only
			STATUS	current
			::= { hmWanMbus92 7 }

hmWanMbus92VIF01		OBJECT-TYPE
			SYNTAX	INTEGER
			MAX-ACCESS	read-only
			STATUS	current
			::= { hmWanMbus92 8 }

hmWanMbus92Value01		OBJECT-TYPE
			SYNTAX	INTEGER
			MAX-ACCESS	read-only
			STATUS	current
			::= { hmWanMbus92 9 }

hmWanMbus92VIF02		OBJECT-TYPE
			SYNTAX	INTEGER
			MAX-ACCESS	read-only
			STATUS	current
			::= { hmWanMbus92 10 }

hmWanMbus92Value02		OBJECT-TYPE
			SYNTAX	INTEGER
			MAX-ACCESS	read-only
			STATUS	current
			::= { hmWanMbus92 11 }

hmWanMbus92VIF03		OBJECT-TYPE
			SYNTAX	INTEGER
			MAX-ACCESS	read-only
			STATUS	current
			::= { hmWanMbus92 12 }

hmWanMbus92Value03		OBJECT-TYPE
			SYNTAX	INTEGER
			MAX-ACCESS	read-only
			STATUS	current
			::= { hmWanMbus92 13 }

hmWanMbus92VIF04		OBJECT-TYPE
			SYNTAX	INTEGER
			MAX-ACCESS	read-only
			STATUS	current
			::= { hmWanMbus92 14 }

hmWanMbus92Value04		OBJECT-TYPE
			SYNTAX	INTEGER
			MAX-ACCESS	read-only
			STATUS	current
			::= { hmWanMbus92 15 }

hmWanMbus92VIF05		OBJECT-TYPE
			SYNTAX	INTEGER
			MAX-ACCESS	read-only
			STATUS	current
			::= { hmWanMbus92 16 }

hmWanMbus92Value05		OBJECT-TYPE
			SYNTAX	INTEGER
			MAX-ACCESS	read-only
			STATUS	current
			::= { hmWanMbus92 17 }

hmWanMbus92VIF06		OBJECT-TYPE
			SYNTAX	INTEGER
			MAX-ACCESS	read-only
			STATUS	current
			::= { hmWanMbus92 18 }

hmWanMbus92Value06		OBJECT-TYPE
			SYNTAX	INTEGER
			MAX-ACCESS	read-only
			STATUS	current
			::= { hmWanMbus92 19 }

hmWanMbus92VIF07		OBJECT-TYPE
			SYNTAX	INTEGER
			MAX-ACCESS	read-only
			STATUS	current
			::= { hmWanMbus92 20 }

hmWanMbus92Value07		OBJECT-TYPE
			SYNTAX	INTEGER
			MAX-ACCESS	read-only
			STATUS	current
			::= { hmWanMbus92 21 }

hmWanMbus92VIF08		OBJECT-TYPE
			SYNTAX	INTEGER
			MAX-ACCESS	read-only
			STATUS	current
			::= { hmWanMbus92 22 }

hmWanMbus92Value08		OBJECT-TYPE
			SYNTAX	INTEGER
			MAX-ACCESS	read-only
			STATUS	current
			::= { hmWanMbus92 23 }

hmWanMbus92VIF09		OBJECT-TYPE
			SYNTAX	INTEGER
			MAX-ACCESS	read-only
			STATUS	current
			::= { hmWanMbus92 24 }

hmWanMbus92Value09		OBJECT-TYPE
			SYNTAX	INTEGER
			MAX-ACCESS	read-only
			STATUS	current
			::= { hmWanMbus92 25 }

hmWanMbus92VIF0A		OBJECT-TYPE
			SYNTAX	INTEGER
			MAX-ACCESS	read-only
			STATUS	current
			::= { hmWanMbus92 26 }

hmWanMbus92Value0A		OBJECT-TYPE
			SYNTAX	INTEGER
			MAX-ACCESS	read-only
			STATUS	current
			::= { hmWanMbus92 27 }

hmWanMbus92VIF0B		OBJECT-TYPE
			SYNTAX	INTEGER
			MAX-ACCESS	read-only
			STATUS	current
			::= { hmWanMbus92 28 }

hmWanMbus92Value0B		OBJECT-TYPE
			SYNTAX	INTEGER
			MAX-ACCESS	read-only
			STATUS	current
			::= { hmWanMbus92 29 }

hmWanMbus92VIF0C		OBJECT-TYPE
			SYNTAX	INTEGER
			MAX-ACCESS	read-only
			STATUS	current
			::= { hmWanMbus92 30 }

hmWanMbus92Value0C		OBJECT-TYPE
			SYNTAX	INTEGER
			MAX-ACCESS	read-only
			STATUS	current
			::= { hmWanMbus92 31 }

hmWanMbus92VIF0D		OBJECT-TYPE
			SYNTAX	INTEGER
			MAX-ACCESS	read-only
			STATUS	current
			::= { hmWanMbus92 32 }

hmWanMbus92Value0D		OBJECT-TYPE
			SYNTAX	INTEGER
			MAX-ACCESS	read-only
			STATUS	current
			::= { hmWanMbus92 33 }

hmWanMbus92VIF0E		OBJECT-TYPE
			SYNTAX	INTEGER
			MAX-ACCESS	read-only
			STATUS	current
			::= { hmWanMbus92 34 }

hmWanMbus92Value0E		OBJECT-TYPE
			SYNTAX	INTEGER
			MAX-ACCESS	read-only
			STATUS	current
			::= { hmWanMbus92 35 }

hmWanMbus92VIF0F		OBJECT-TYPE
			SYNTAX	INTEGER
			MAX-ACCESS	read-only
			STATUS	current
			::= { hmWanMbus92 36 }

hmWanMbus92Value0F		OBJECT-TYPE
			SYNTAX	INTEGER
			MAX-ACCESS	read-only
			STATUS	current
			::= { hmWanMbus92 37 }

hmWanMbus92VIF10		OBJECT-TYPE
			SYNTAX	INTEGER
			MAX-ACCESS	read-only
			STATUS	current
			::= { hmWanMbus92 38 }

hmWanMbus92Value10		OBJECT-TYPE
			SYNTAX	INTEGER
			MAX-ACCESS	read-only
			STATUS	current
			::= { hmWanMbus92 39 }

hmWanMbus92VIF11		OBJECT-TYPE
			SYNTAX	INTEGER
			MAX-ACCESS	read-only
			STATUS	current
			::= { hmWanMbus92 40 }

hmWanMbus92Value11		OBJECT-TYPE
			SYNTAX	INTEGER
			MAX-ACCESS	read-only
			STATUS	current
			::= { hmWanMbus92 41 }

hmWanMbus92VIF12		OBJECT-TYPE
			SYNTAX	INTEGER
			MAX-ACCESS	read-only
			STATUS	current
			::= { hmWanMbus92 42 }

hmWanMbus92Value12		OBJECT-TYPE
			SYNTAX	INTEGER
			MAX-ACCESS	read-only
			STATUS	current
			::= { hmWanMbus92 43 }

hmWanMbus92VIF13		OBJECT-TYPE
			SYNTAX	INTEGER
			MAX-ACCESS	read-only
			STATUS	current
			::= { hmWanMbus92 44 }

hmWanMbus92Value13		OBJECT-TYPE
			SYNTAX	INTEGER
			MAX-ACCESS	read-only
			STATUS	current
			::= { hmWanMbus92 45 }

hmWanMbus92VIF14		OBJECT-TYPE
			SYNTAX	INTEGER
			MAX-ACCESS	read-only
			STATUS	current
			::= { hmWanMbus92 46 }

hmWanMbus92Value14		OBJECT-TYPE
			SYNTAX	INTEGER
			MAX-ACCESS	read-only
			STATUS	current
			::= { hmWanMbus92 47 }

hmWanMbus92VIF15		OBJECT-TYPE
			SYNTAX	INTEGER
			MAX-ACCESS	read-only
			STATUS	current
			::= { hmWanMbus92 48 }

hmWanMbus92Value15		OBJECT-TYPE
			SYNTAX	INTEGER
			MAX-ACCESS	read-only
			STATUS	current
			::= { hmWanMbus92 49 }

hmWanMbus92VIF16		OBJECT-TYPE
			SYNTAX	INTEGER
			MAX-ACCESS	read-only
			STATUS	current
			::= { hmWanMbus92 50 }

hmWanMbus92Value16		OBJECT-TYPE
			SYNTAX	INTEGER
			MAX-ACCESS	read-only
			STATUS	current
			::= { hmWanMbus92 51 }

hmWanMbus92VIF17		OBJECT-TYPE
			SYNTAX	INTEGER
			MAX-ACCESS	read-only
			STATUS	current
			::= { hmWanMbus92 52 }

hmWanMbus92Value17		OBJECT-TYPE
			SYNTAX	INTEGER
			MAX-ACCESS	read-only
			STATUS	current
			::= { hmWanMbus92 53 }

hmWanMbus92VIF18		OBJECT-TYPE
			SYNTAX	INTEGER
			MAX-ACCESS	read-only
			STATUS	current
			::= { hmWanMbus92 54 }

hmWanMbus92Value18		OBJECT-TYPE
			SYNTAX	INTEGER
			MAX-ACCESS	read-only
			STATUS	current
			::= { hmWanMbus92 55 }

hmWanMbus92VIF19		OBJECT-TYPE
			SYNTAX	INTEGER
			MAX-ACCESS	read-only
			STATUS	current
			::= { hmWanMbus92 56 }

hmWanMbus92Value19		OBJECT-TYPE
			SYNTAX	INTEGER
			MAX-ACCESS	read-only
			STATUS	current
			::= { hmWanMbus92 57 }

hmWanMbus92VIF1A		OBJECT-TYPE
			SYNTAX	INTEGER
			MAX-ACCESS	read-only
			STATUS	current
			::= { hmWanMbus92 58 }

hmWanMbus92Value1A		OBJECT-TYPE
			SYNTAX	INTEGER
			MAX-ACCESS	read-only
			STATUS	current
			::= { hmWanMbus92 59 }

hmWanMbus92VIF1B		OBJECT-TYPE
			SYNTAX	INTEGER
			MAX-ACCESS	read-only
			STATUS	current
			::= { hmWanMbus92 60 }

hmWanMbus92Value1B		OBJECT-TYPE
			SYNTAX	INTEGER
			MAX-ACCESS	read-only
			STATUS	current
			::= { hmWanMbus92 61 }

hmWanMbus92VIF1C		OBJECT-TYPE
			SYNTAX	INTEGER
			MAX-ACCESS	read-only
			STATUS	current
			::= { hmWanMbus92 62 }

hmWanMbus92Value1C		OBJECT-TYPE
			SYNTAX	INTEGER
			MAX-ACCESS	read-only
			STATUS	current
			::= { hmWanMbus92 63 }

hmWanMbus92VIF1D		OBJECT-TYPE
			SYNTAX	INTEGER
			MAX-ACCESS	read-only
			STATUS	current
			::= { hmWanMbus92 64 }

hmWanMbus92Value1D		OBJECT-TYPE
			SYNTAX	INTEGER
			MAX-ACCESS	read-only
			STATUS	current
			::= { hmWanMbus92 65 }

hmWanMbus92VIF1E		OBJECT-TYPE
			SYNTAX	INTEGER
			MAX-ACCESS	read-only
			STATUS	current
			::= { hmWanMbus92 66 }

hmWanMbus92Value1E		OBJECT-TYPE
			SYNTAX	INTEGER
			MAX-ACCESS	read-only
			STATUS	current
			::= { hmWanMbus92 67 }

hmWanMbus92VIF1F		OBJECT-TYPE
			SYNTAX	INTEGER
			MAX-ACCESS	read-only
			STATUS	current
			::= { hmWanMbus92 68 }

hmWanMbus92Value1F		OBJECT-TYPE
			SYNTAX	INTEGER
			MAX-ACCESS	read-only
			STATUS	current
			::= { hmWanMbus92 69 }

hmWanMbus92VIF20		OBJECT-TYPE
			SYNTAX	INTEGER
			MAX-ACCESS	read-only
			STATUS	current
			::= { hmWanMbus92 70 }

hmWanMbus92Value20		OBJECT-TYPE
			SYNTAX	INTEGER
			MAX-ACCESS	read-only
			STATUS	current
			::= { hmWanMbus92 71 }

hmWanMbus92VIF21		OBJECT-TYPE
			SYNTAX	INTEGER
			MAX-ACCESS	read-only
			STATUS	current
			::= { hmWanMbus92 72 }

hmWanMbus92Value21		OBJECT-TYPE
			SYNTAX	INTEGER
			MAX-ACCESS	read-only
			STATUS	current
			::= { hmWanMbus92 73 }

hmWanMbus92VIF22		OBJECT-TYPE
			SYNTAX	INTEGER
			MAX-ACCESS	read-only
			STATUS	current
			::= { hmWanMbus92 74 }

hmWanMbus92Value22		OBJECT-TYPE
			SYNTAX	INTEGER
			MAX-ACCESS	read-only
			STATUS	current
			::= { hmWanMbus92 75 }

hmWanMbus92VIF23		OBJECT-TYPE
			SYNTAX	INTEGER
			MAX-ACCESS	read-only
			STATUS	current
			::= { hmWanMbus92 76 }

hmWanMbus92Value23		OBJECT-TYPE
			SYNTAX	INTEGER
			MAX-ACCESS	read-only
			STATUS	current
			::= { hmWanMbus92 77 }

hmWanMbus92VIF24		OBJECT-TYPE
			SYNTAX	INTEGER
			MAX-ACCESS	read-only
			STATUS	current
			::= { hmWanMbus92 78 }

hmWanMbus92Value24		OBJECT-TYPE
			SYNTAX	INTEGER
			MAX-ACCESS	read-only
			STATUS	current
			::= { hmWanMbus92 79 }

hmWanMbus92VIF25		OBJECT-TYPE
			SYNTAX	INTEGER
			MAX-ACCESS	read-only
			STATUS	current
			::= { hmWanMbus92 80 }

hmWanMbus92Value25		OBJECT-TYPE
			SYNTAX	INTEGER
			MAX-ACCESS	read-only
			STATUS	current
			::= { hmWanMbus92 81 }

hmWanMbus92VIF26		OBJECT-TYPE
			SYNTAX	INTEGER
			MAX-ACCESS	read-only
			STATUS	current
			::= { hmWanMbus92 82 }

hmWanMbus92Value26		OBJECT-TYPE
			SYNTAX	INTEGER
			MAX-ACCESS	read-only
			STATUS	current
			::= { hmWanMbus92 83 }

hmWanMbus92VIF27		OBJECT-TYPE
			SYNTAX	INTEGER
			MAX-ACCESS	read-only
			STATUS	current
			::= { hmWanMbus92 84 }

hmWanMbus92Value27		OBJECT-TYPE
			SYNTAX	INTEGER
			MAX-ACCESS	read-only
			STATUS	current
			::= { hmWanMbus92 85 }

hmWanMbus92VIF28		OBJECT-TYPE
			SYNTAX	INTEGER
			MAX-ACCESS	read-only
			STATUS	current
			::= { hmWanMbus92 86 }

hmWanMbus92Value28		OBJECT-TYPE
			SYNTAX	INTEGER
			MAX-ACCESS	read-only
			STATUS	current
			::= { hmWanMbus92 87 }

hmWanMbus92VIF29		OBJECT-TYPE
			SYNTAX	INTEGER
			MAX-ACCESS	read-only
			STATUS	current
			::= { hmWanMbus92 88 }

hmWanMbus92Value29		OBJECT-TYPE
			SYNTAX	INTEGER
			MAX-ACCESS	read-only
			STATUS	current
			::= { hmWanMbus92 89 }

hmWanMbus92VIF2A		OBJECT-TYPE
			SYNTAX	INTEGER
			MAX-ACCESS	read-only
			STATUS	current
			::= { hmWanMbus92 90 }

hmWanMbus92Value2A		OBJECT-TYPE
			SYNTAX	INTEGER
			MAX-ACCESS	read-only
			STATUS	current
			::= { hmWanMbus92 91 }

hmWanMbus92VIF2B		OBJECT-TYPE
			SYNTAX	INTEGER
			MAX-ACCESS	read-only
			STATUS	current
			::= { hmWanMbus92 92 }

hmWanMbus92Value2B		OBJECT-TYPE
			SYNTAX	INTEGER
			MAX-ACCESS	read-only
			STATUS	current
			::= { hmWanMbus92 93 }

hmWanMbus92VIF2C		OBJECT-TYPE
			SYNTAX	INTEGER
			MAX-ACCESS	read-only
			STATUS	current
			::= { hmWanMbus92 94 }

hmWanMbus92Value2C		OBJECT-TYPE
			SYNTAX	INTEGER
			MAX-ACCESS	read-only
			STATUS	current
			::= { hmWanMbus92 95 }

hmWanMbus92VIF2D		OBJECT-TYPE
			SYNTAX	INTEGER
			MAX-ACCESS	read-only
			STATUS	current
			::= { hmWanMbus92 96 }

hmWanMbus92Value2D		OBJECT-TYPE
			SYNTAX	INTEGER
			MAX-ACCESS	read-only
			STATUS	current
			::= { hmWanMbus92 97 }

hmWanMbus92VIF2E		OBJECT-TYPE
			SYNTAX	INTEGER
			MAX-ACCESS	read-only
			STATUS	current
			::= { hmWanMbus92 98 }

hmWanMbus92Value2E		OBJECT-TYPE
			SYNTAX	INTEGER
			MAX-ACCESS	read-only
			STATUS	current
			::= { hmWanMbus92 99 }

hmWanMbus92VIF2F		OBJECT-TYPE
			SYNTAX	INTEGER
			MAX-ACCESS	read-only
			STATUS	current
			::= { hmWanMbus92 100 }

hmWanMbus92Value2F		OBJECT-TYPE
			SYNTAX	INTEGER
			MAX-ACCESS	read-only
			STATUS	current
			::= { hmWanMbus92 101 }

hmWanMbus93			OBJECT IDENTIFIER ::= { hmWanMbus 147 }

hmWanMbus93IdNumber		OBJECT-TYPE
			SYNTAX	Gauge32
			MAX-ACCESS	read-only
			STATUS	current
			::= { hmWanMbus93 1 }

hmWanMbus93Manufacturer	OBJECT-TYPE
			SYNTAX	Gauge32
			MAX-ACCESS	read-only
			STATUS	current
			::= { hmWanMbus93 2 }

hmWanMbus93Version		OBJECT-TYPE
			SYNTAX	Gauge32
			MAX-ACCESS	read-only
			STATUS	current
			::= { hmWanMbus93 3 }

hmWanMbus93Medium		OBJECT-TYPE
			SYNTAX	Gauge32
			MAX-ACCESS	read-only
			STATUS	current
			::= { hmWanMbus93 4 }

hmWanMbus93Status		OBJECT-TYPE
			SYNTAX	Gauge32
			MAX-ACCESS	read-only
			STATUS	current
			::= { hmWanMbus93 5 }

hmWanMbus93VIF00		OBJECT-TYPE
			SYNTAX	INTEGER
			MAX-ACCESS	read-only
			STATUS	current
			::= { hmWanMbus93 6 }

hmWanMbus93Value00		OBJECT-TYPE
			SYNTAX	INTEGER
			MAX-ACCESS	read-only
			STATUS	current
			::= { hmWanMbus93 7 }

hmWanMbus93VIF01		OBJECT-TYPE
			SYNTAX	INTEGER
			MAX-ACCESS	read-only
			STATUS	current
			::= { hmWanMbus93 8 }

hmWanMbus93Value01		OBJECT-TYPE
			SYNTAX	INTEGER
			MAX-ACCESS	read-only
			STATUS	current
			::= { hmWanMbus93 9 }

hmWanMbus93VIF02		OBJECT-TYPE
			SYNTAX	INTEGER
			MAX-ACCESS	read-only
			STATUS	current
			::= { hmWanMbus93 10 }

hmWanMbus93Value02		OBJECT-TYPE
			SYNTAX	INTEGER
			MAX-ACCESS	read-only
			STATUS	current
			::= { hmWanMbus93 11 }

hmWanMbus93VIF03		OBJECT-TYPE
			SYNTAX	INTEGER
			MAX-ACCESS	read-only
			STATUS	current
			::= { hmWanMbus93 12 }

hmWanMbus93Value03		OBJECT-TYPE
			SYNTAX	INTEGER
			MAX-ACCESS	read-only
			STATUS	current
			::= { hmWanMbus93 13 }

hmWanMbus93VIF04		OBJECT-TYPE
			SYNTAX	INTEGER
			MAX-ACCESS	read-only
			STATUS	current
			::= { hmWanMbus93 14 }

hmWanMbus93Value04		OBJECT-TYPE
			SYNTAX	INTEGER
			MAX-ACCESS	read-only
			STATUS	current
			::= { hmWanMbus93 15 }

hmWanMbus93VIF05		OBJECT-TYPE
			SYNTAX	INTEGER
			MAX-ACCESS	read-only
			STATUS	current
			::= { hmWanMbus93 16 }

hmWanMbus93Value05		OBJECT-TYPE
			SYNTAX	INTEGER
			MAX-ACCESS	read-only
			STATUS	current
			::= { hmWanMbus93 17 }

hmWanMbus93VIF06		OBJECT-TYPE
			SYNTAX	INTEGER
			MAX-ACCESS	read-only
			STATUS	current
			::= { hmWanMbus93 18 }

hmWanMbus93Value06		OBJECT-TYPE
			SYNTAX	INTEGER
			MAX-ACCESS	read-only
			STATUS	current
			::= { hmWanMbus93 19 }

hmWanMbus93VIF07		OBJECT-TYPE
			SYNTAX	INTEGER
			MAX-ACCESS	read-only
			STATUS	current
			::= { hmWanMbus93 20 }

hmWanMbus93Value07		OBJECT-TYPE
			SYNTAX	INTEGER
			MAX-ACCESS	read-only
			STATUS	current
			::= { hmWanMbus93 21 }

hmWanMbus93VIF08		OBJECT-TYPE
			SYNTAX	INTEGER
			MAX-ACCESS	read-only
			STATUS	current
			::= { hmWanMbus93 22 }

hmWanMbus93Value08		OBJECT-TYPE
			SYNTAX	INTEGER
			MAX-ACCESS	read-only
			STATUS	current
			::= { hmWanMbus93 23 }

hmWanMbus93VIF09		OBJECT-TYPE
			SYNTAX	INTEGER
			MAX-ACCESS	read-only
			STATUS	current
			::= { hmWanMbus93 24 }

hmWanMbus93Value09		OBJECT-TYPE
			SYNTAX	INTEGER
			MAX-ACCESS	read-only
			STATUS	current
			::= { hmWanMbus93 25 }

hmWanMbus93VIF0A		OBJECT-TYPE
			SYNTAX	INTEGER
			MAX-ACCESS	read-only
			STATUS	current
			::= { hmWanMbus93 26 }

hmWanMbus93Value0A		OBJECT-TYPE
			SYNTAX	INTEGER
			MAX-ACCESS	read-only
			STATUS	current
			::= { hmWanMbus93 27 }

hmWanMbus93VIF0B		OBJECT-TYPE
			SYNTAX	INTEGER
			MAX-ACCESS	read-only
			STATUS	current
			::= { hmWanMbus93 28 }

hmWanMbus93Value0B		OBJECT-TYPE
			SYNTAX	INTEGER
			MAX-ACCESS	read-only
			STATUS	current
			::= { hmWanMbus93 29 }

hmWanMbus93VIF0C		OBJECT-TYPE
			SYNTAX	INTEGER
			MAX-ACCESS	read-only
			STATUS	current
			::= { hmWanMbus93 30 }

hmWanMbus93Value0C		OBJECT-TYPE
			SYNTAX	INTEGER
			MAX-ACCESS	read-only
			STATUS	current
			::= { hmWanMbus93 31 }

hmWanMbus93VIF0D		OBJECT-TYPE
			SYNTAX	INTEGER
			MAX-ACCESS	read-only
			STATUS	current
			::= { hmWanMbus93 32 }

hmWanMbus93Value0D		OBJECT-TYPE
			SYNTAX	INTEGER
			MAX-ACCESS	read-only
			STATUS	current
			::= { hmWanMbus93 33 }

hmWanMbus93VIF0E		OBJECT-TYPE
			SYNTAX	INTEGER
			MAX-ACCESS	read-only
			STATUS	current
			::= { hmWanMbus93 34 }

hmWanMbus93Value0E		OBJECT-TYPE
			SYNTAX	INTEGER
			MAX-ACCESS	read-only
			STATUS	current
			::= { hmWanMbus93 35 }

hmWanMbus93VIF0F		OBJECT-TYPE
			SYNTAX	INTEGER
			MAX-ACCESS	read-only
			STATUS	current
			::= { hmWanMbus93 36 }

hmWanMbus93Value0F		OBJECT-TYPE
			SYNTAX	INTEGER
			MAX-ACCESS	read-only
			STATUS	current
			::= { hmWanMbus93 37 }

hmWanMbus93VIF10		OBJECT-TYPE
			SYNTAX	INTEGER
			MAX-ACCESS	read-only
			STATUS	current
			::= { hmWanMbus93 38 }

hmWanMbus93Value10		OBJECT-TYPE
			SYNTAX	INTEGER
			MAX-ACCESS	read-only
			STATUS	current
			::= { hmWanMbus93 39 }

hmWanMbus93VIF11		OBJECT-TYPE
			SYNTAX	INTEGER
			MAX-ACCESS	read-only
			STATUS	current
			::= { hmWanMbus93 40 }

hmWanMbus93Value11		OBJECT-TYPE
			SYNTAX	INTEGER
			MAX-ACCESS	read-only
			STATUS	current
			::= { hmWanMbus93 41 }

hmWanMbus93VIF12		OBJECT-TYPE
			SYNTAX	INTEGER
			MAX-ACCESS	read-only
			STATUS	current
			::= { hmWanMbus93 42 }

hmWanMbus93Value12		OBJECT-TYPE
			SYNTAX	INTEGER
			MAX-ACCESS	read-only
			STATUS	current
			::= { hmWanMbus93 43 }

hmWanMbus93VIF13		OBJECT-TYPE
			SYNTAX	INTEGER
			MAX-ACCESS	read-only
			STATUS	current
			::= { hmWanMbus93 44 }

hmWanMbus93Value13		OBJECT-TYPE
			SYNTAX	INTEGER
			MAX-ACCESS	read-only
			STATUS	current
			::= { hmWanMbus93 45 }

hmWanMbus93VIF14		OBJECT-TYPE
			SYNTAX	INTEGER
			MAX-ACCESS	read-only
			STATUS	current
			::= { hmWanMbus93 46 }

hmWanMbus93Value14		OBJECT-TYPE
			SYNTAX	INTEGER
			MAX-ACCESS	read-only
			STATUS	current
			::= { hmWanMbus93 47 }

hmWanMbus93VIF15		OBJECT-TYPE
			SYNTAX	INTEGER
			MAX-ACCESS	read-only
			STATUS	current
			::= { hmWanMbus93 48 }

hmWanMbus93Value15		OBJECT-TYPE
			SYNTAX	INTEGER
			MAX-ACCESS	read-only
			STATUS	current
			::= { hmWanMbus93 49 }

hmWanMbus93VIF16		OBJECT-TYPE
			SYNTAX	INTEGER
			MAX-ACCESS	read-only
			STATUS	current
			::= { hmWanMbus93 50 }

hmWanMbus93Value16		OBJECT-TYPE
			SYNTAX	INTEGER
			MAX-ACCESS	read-only
			STATUS	current
			::= { hmWanMbus93 51 }

hmWanMbus93VIF17		OBJECT-TYPE
			SYNTAX	INTEGER
			MAX-ACCESS	read-only
			STATUS	current
			::= { hmWanMbus93 52 }

hmWanMbus93Value17		OBJECT-TYPE
			SYNTAX	INTEGER
			MAX-ACCESS	read-only
			STATUS	current
			::= { hmWanMbus93 53 }

hmWanMbus93VIF18		OBJECT-TYPE
			SYNTAX	INTEGER
			MAX-ACCESS	read-only
			STATUS	current
			::= { hmWanMbus93 54 }

hmWanMbus93Value18		OBJECT-TYPE
			SYNTAX	INTEGER
			MAX-ACCESS	read-only
			STATUS	current
			::= { hmWanMbus93 55 }

hmWanMbus93VIF19		OBJECT-TYPE
			SYNTAX	INTEGER
			MAX-ACCESS	read-only
			STATUS	current
			::= { hmWanMbus93 56 }

hmWanMbus93Value19		OBJECT-TYPE
			SYNTAX	INTEGER
			MAX-ACCESS	read-only
			STATUS	current
			::= { hmWanMbus93 57 }

hmWanMbus93VIF1A		OBJECT-TYPE
			SYNTAX	INTEGER
			MAX-ACCESS	read-only
			STATUS	current
			::= { hmWanMbus93 58 }

hmWanMbus93Value1A		OBJECT-TYPE
			SYNTAX	INTEGER
			MAX-ACCESS	read-only
			STATUS	current
			::= { hmWanMbus93 59 }

hmWanMbus93VIF1B		OBJECT-TYPE
			SYNTAX	INTEGER
			MAX-ACCESS	read-only
			STATUS	current
			::= { hmWanMbus93 60 }

hmWanMbus93Value1B		OBJECT-TYPE
			SYNTAX	INTEGER
			MAX-ACCESS	read-only
			STATUS	current
			::= { hmWanMbus93 61 }

hmWanMbus93VIF1C		OBJECT-TYPE
			SYNTAX	INTEGER
			MAX-ACCESS	read-only
			STATUS	current
			::= { hmWanMbus93 62 }

hmWanMbus93Value1C		OBJECT-TYPE
			SYNTAX	INTEGER
			MAX-ACCESS	read-only
			STATUS	current
			::= { hmWanMbus93 63 }

hmWanMbus93VIF1D		OBJECT-TYPE
			SYNTAX	INTEGER
			MAX-ACCESS	read-only
			STATUS	current
			::= { hmWanMbus93 64 }

hmWanMbus93Value1D		OBJECT-TYPE
			SYNTAX	INTEGER
			MAX-ACCESS	read-only
			STATUS	current
			::= { hmWanMbus93 65 }

hmWanMbus93VIF1E		OBJECT-TYPE
			SYNTAX	INTEGER
			MAX-ACCESS	read-only
			STATUS	current
			::= { hmWanMbus93 66 }

hmWanMbus93Value1E		OBJECT-TYPE
			SYNTAX	INTEGER
			MAX-ACCESS	read-only
			STATUS	current
			::= { hmWanMbus93 67 }

hmWanMbus93VIF1F		OBJECT-TYPE
			SYNTAX	INTEGER
			MAX-ACCESS	read-only
			STATUS	current
			::= { hmWanMbus93 68 }

hmWanMbus93Value1F		OBJECT-TYPE
			SYNTAX	INTEGER
			MAX-ACCESS	read-only
			STATUS	current
			::= { hmWanMbus93 69 }

hmWanMbus93VIF20		OBJECT-TYPE
			SYNTAX	INTEGER
			MAX-ACCESS	read-only
			STATUS	current
			::= { hmWanMbus93 70 }

hmWanMbus93Value20		OBJECT-TYPE
			SYNTAX	INTEGER
			MAX-ACCESS	read-only
			STATUS	current
			::= { hmWanMbus93 71 }

hmWanMbus93VIF21		OBJECT-TYPE
			SYNTAX	INTEGER
			MAX-ACCESS	read-only
			STATUS	current
			::= { hmWanMbus93 72 }

hmWanMbus93Value21		OBJECT-TYPE
			SYNTAX	INTEGER
			MAX-ACCESS	read-only
			STATUS	current
			::= { hmWanMbus93 73 }

hmWanMbus93VIF22		OBJECT-TYPE
			SYNTAX	INTEGER
			MAX-ACCESS	read-only
			STATUS	current
			::= { hmWanMbus93 74 }

hmWanMbus93Value22		OBJECT-TYPE
			SYNTAX	INTEGER
			MAX-ACCESS	read-only
			STATUS	current
			::= { hmWanMbus93 75 }

hmWanMbus93VIF23		OBJECT-TYPE
			SYNTAX	INTEGER
			MAX-ACCESS	read-only
			STATUS	current
			::= { hmWanMbus93 76 }

hmWanMbus93Value23		OBJECT-TYPE
			SYNTAX	INTEGER
			MAX-ACCESS	read-only
			STATUS	current
			::= { hmWanMbus93 77 }

hmWanMbus93VIF24		OBJECT-TYPE
			SYNTAX	INTEGER
			MAX-ACCESS	read-only
			STATUS	current
			::= { hmWanMbus93 78 }

hmWanMbus93Value24		OBJECT-TYPE
			SYNTAX	INTEGER
			MAX-ACCESS	read-only
			STATUS	current
			::= { hmWanMbus93 79 }

hmWanMbus93VIF25		OBJECT-TYPE
			SYNTAX	INTEGER
			MAX-ACCESS	read-only
			STATUS	current
			::= { hmWanMbus93 80 }

hmWanMbus93Value25		OBJECT-TYPE
			SYNTAX	INTEGER
			MAX-ACCESS	read-only
			STATUS	current
			::= { hmWanMbus93 81 }

hmWanMbus93VIF26		OBJECT-TYPE
			SYNTAX	INTEGER
			MAX-ACCESS	read-only
			STATUS	current
			::= { hmWanMbus93 82 }

hmWanMbus93Value26		OBJECT-TYPE
			SYNTAX	INTEGER
			MAX-ACCESS	read-only
			STATUS	current
			::= { hmWanMbus93 83 }

hmWanMbus93VIF27		OBJECT-TYPE
			SYNTAX	INTEGER
			MAX-ACCESS	read-only
			STATUS	current
			::= { hmWanMbus93 84 }

hmWanMbus93Value27		OBJECT-TYPE
			SYNTAX	INTEGER
			MAX-ACCESS	read-only
			STATUS	current
			::= { hmWanMbus93 85 }

hmWanMbus93VIF28		OBJECT-TYPE
			SYNTAX	INTEGER
			MAX-ACCESS	read-only
			STATUS	current
			::= { hmWanMbus93 86 }

hmWanMbus93Value28		OBJECT-TYPE
			SYNTAX	INTEGER
			MAX-ACCESS	read-only
			STATUS	current
			::= { hmWanMbus93 87 }

hmWanMbus93VIF29		OBJECT-TYPE
			SYNTAX	INTEGER
			MAX-ACCESS	read-only
			STATUS	current
			::= { hmWanMbus93 88 }

hmWanMbus93Value29		OBJECT-TYPE
			SYNTAX	INTEGER
			MAX-ACCESS	read-only
			STATUS	current
			::= { hmWanMbus93 89 }

hmWanMbus93VIF2A		OBJECT-TYPE
			SYNTAX	INTEGER
			MAX-ACCESS	read-only
			STATUS	current
			::= { hmWanMbus93 90 }

hmWanMbus93Value2A		OBJECT-TYPE
			SYNTAX	INTEGER
			MAX-ACCESS	read-only
			STATUS	current
			::= { hmWanMbus93 91 }

hmWanMbus93VIF2B		OBJECT-TYPE
			SYNTAX	INTEGER
			MAX-ACCESS	read-only
			STATUS	current
			::= { hmWanMbus93 92 }

hmWanMbus93Value2B		OBJECT-TYPE
			SYNTAX	INTEGER
			MAX-ACCESS	read-only
			STATUS	current
			::= { hmWanMbus93 93 }

hmWanMbus93VIF2C		OBJECT-TYPE
			SYNTAX	INTEGER
			MAX-ACCESS	read-only
			STATUS	current
			::= { hmWanMbus93 94 }

hmWanMbus93Value2C		OBJECT-TYPE
			SYNTAX	INTEGER
			MAX-ACCESS	read-only
			STATUS	current
			::= { hmWanMbus93 95 }

hmWanMbus93VIF2D		OBJECT-TYPE
			SYNTAX	INTEGER
			MAX-ACCESS	read-only
			STATUS	current
			::= { hmWanMbus93 96 }

hmWanMbus93Value2D		OBJECT-TYPE
			SYNTAX	INTEGER
			MAX-ACCESS	read-only
			STATUS	current
			::= { hmWanMbus93 97 }

hmWanMbus93VIF2E		OBJECT-TYPE
			SYNTAX	INTEGER
			MAX-ACCESS	read-only
			STATUS	current
			::= { hmWanMbus93 98 }

hmWanMbus93Value2E		OBJECT-TYPE
			SYNTAX	INTEGER
			MAX-ACCESS	read-only
			STATUS	current
			::= { hmWanMbus93 99 }

hmWanMbus93VIF2F		OBJECT-TYPE
			SYNTAX	INTEGER
			MAX-ACCESS	read-only
			STATUS	current
			::= { hmWanMbus93 100 }

hmWanMbus93Value2F		OBJECT-TYPE
			SYNTAX	INTEGER
			MAX-ACCESS	read-only
			STATUS	current
			::= { hmWanMbus93 101 }

hmWanMbus94			OBJECT IDENTIFIER ::= { hmWanMbus 148 }

hmWanMbus94IdNumber		OBJECT-TYPE
			SYNTAX	Gauge32
			MAX-ACCESS	read-only
			STATUS	current
			::= { hmWanMbus94 1 }

hmWanMbus94Manufacturer	OBJECT-TYPE
			SYNTAX	Gauge32
			MAX-ACCESS	read-only
			STATUS	current
			::= { hmWanMbus94 2 }

hmWanMbus94Version		OBJECT-TYPE
			SYNTAX	Gauge32
			MAX-ACCESS	read-only
			STATUS	current
			::= { hmWanMbus94 3 }

hmWanMbus94Medium		OBJECT-TYPE
			SYNTAX	Gauge32
			MAX-ACCESS	read-only
			STATUS	current
			::= { hmWanMbus94 4 }

hmWanMbus94Status		OBJECT-TYPE
			SYNTAX	Gauge32
			MAX-ACCESS	read-only
			STATUS	current
			::= { hmWanMbus94 5 }

hmWanMbus94VIF00		OBJECT-TYPE
			SYNTAX	INTEGER
			MAX-ACCESS	read-only
			STATUS	current
			::= { hmWanMbus94 6 }

hmWanMbus94Value00		OBJECT-TYPE
			SYNTAX	INTEGER
			MAX-ACCESS	read-only
			STATUS	current
			::= { hmWanMbus94 7 }

hmWanMbus94VIF01		OBJECT-TYPE
			SYNTAX	INTEGER
			MAX-ACCESS	read-only
			STATUS	current
			::= { hmWanMbus94 8 }

hmWanMbus94Value01		OBJECT-TYPE
			SYNTAX	INTEGER
			MAX-ACCESS	read-only
			STATUS	current
			::= { hmWanMbus94 9 }

hmWanMbus94VIF02		OBJECT-TYPE
			SYNTAX	INTEGER
			MAX-ACCESS	read-only
			STATUS	current
			::= { hmWanMbus94 10 }

hmWanMbus94Value02		OBJECT-TYPE
			SYNTAX	INTEGER
			MAX-ACCESS	read-only
			STATUS	current
			::= { hmWanMbus94 11 }

hmWanMbus94VIF03		OBJECT-TYPE
			SYNTAX	INTEGER
			MAX-ACCESS	read-only
			STATUS	current
			::= { hmWanMbus94 12 }

hmWanMbus94Value03		OBJECT-TYPE
			SYNTAX	INTEGER
			MAX-ACCESS	read-only
			STATUS	current
			::= { hmWanMbus94 13 }

hmWanMbus94VIF04		OBJECT-TYPE
			SYNTAX	INTEGER
			MAX-ACCESS	read-only
			STATUS	current
			::= { hmWanMbus94 14 }

hmWanMbus94Value04		OBJECT-TYPE
			SYNTAX	INTEGER
			MAX-ACCESS	read-only
			STATUS	current
			::= { hmWanMbus94 15 }

hmWanMbus94VIF05		OBJECT-TYPE
			SYNTAX	INTEGER
			MAX-ACCESS	read-only
			STATUS	current
			::= { hmWanMbus94 16 }

hmWanMbus94Value05		OBJECT-TYPE
			SYNTAX	INTEGER
			MAX-ACCESS	read-only
			STATUS	current
			::= { hmWanMbus94 17 }

hmWanMbus94VIF06		OBJECT-TYPE
			SYNTAX	INTEGER
			MAX-ACCESS	read-only
			STATUS	current
			::= { hmWanMbus94 18 }

hmWanMbus94Value06		OBJECT-TYPE
			SYNTAX	INTEGER
			MAX-ACCESS	read-only
			STATUS	current
			::= { hmWanMbus94 19 }

hmWanMbus94VIF07		OBJECT-TYPE
			SYNTAX	INTEGER
			MAX-ACCESS	read-only
			STATUS	current
			::= { hmWanMbus94 20 }

hmWanMbus94Value07		OBJECT-TYPE
			SYNTAX	INTEGER
			MAX-ACCESS	read-only
			STATUS	current
			::= { hmWanMbus94 21 }

hmWanMbus94VIF08		OBJECT-TYPE
			SYNTAX	INTEGER
			MAX-ACCESS	read-only
			STATUS	current
			::= { hmWanMbus94 22 }

hmWanMbus94Value08		OBJECT-TYPE
			SYNTAX	INTEGER
			MAX-ACCESS	read-only
			STATUS	current
			::= { hmWanMbus94 23 }

hmWanMbus94VIF09		OBJECT-TYPE
			SYNTAX	INTEGER
			MAX-ACCESS	read-only
			STATUS	current
			::= { hmWanMbus94 24 }

hmWanMbus94Value09		OBJECT-TYPE
			SYNTAX	INTEGER
			MAX-ACCESS	read-only
			STATUS	current
			::= { hmWanMbus94 25 }

hmWanMbus94VIF0A		OBJECT-TYPE
			SYNTAX	INTEGER
			MAX-ACCESS	read-only
			STATUS	current
			::= { hmWanMbus94 26 }

hmWanMbus94Value0A		OBJECT-TYPE
			SYNTAX	INTEGER
			MAX-ACCESS	read-only
			STATUS	current
			::= { hmWanMbus94 27 }

hmWanMbus94VIF0B		OBJECT-TYPE
			SYNTAX	INTEGER
			MAX-ACCESS	read-only
			STATUS	current
			::= { hmWanMbus94 28 }

hmWanMbus94Value0B		OBJECT-TYPE
			SYNTAX	INTEGER
			MAX-ACCESS	read-only
			STATUS	current
			::= { hmWanMbus94 29 }

hmWanMbus94VIF0C		OBJECT-TYPE
			SYNTAX	INTEGER
			MAX-ACCESS	read-only
			STATUS	current
			::= { hmWanMbus94 30 }

hmWanMbus94Value0C		OBJECT-TYPE
			SYNTAX	INTEGER
			MAX-ACCESS	read-only
			STATUS	current
			::= { hmWanMbus94 31 }

hmWanMbus94VIF0D		OBJECT-TYPE
			SYNTAX	INTEGER
			MAX-ACCESS	read-only
			STATUS	current
			::= { hmWanMbus94 32 }

hmWanMbus94Value0D		OBJECT-TYPE
			SYNTAX	INTEGER
			MAX-ACCESS	read-only
			STATUS	current
			::= { hmWanMbus94 33 }

hmWanMbus94VIF0E		OBJECT-TYPE
			SYNTAX	INTEGER
			MAX-ACCESS	read-only
			STATUS	current
			::= { hmWanMbus94 34 }

hmWanMbus94Value0E		OBJECT-TYPE
			SYNTAX	INTEGER
			MAX-ACCESS	read-only
			STATUS	current
			::= { hmWanMbus94 35 }

hmWanMbus94VIF0F		OBJECT-TYPE
			SYNTAX	INTEGER
			MAX-ACCESS	read-only
			STATUS	current
			::= { hmWanMbus94 36 }

hmWanMbus94Value0F		OBJECT-TYPE
			SYNTAX	INTEGER
			MAX-ACCESS	read-only
			STATUS	current
			::= { hmWanMbus94 37 }

hmWanMbus94VIF10		OBJECT-TYPE
			SYNTAX	INTEGER
			MAX-ACCESS	read-only
			STATUS	current
			::= { hmWanMbus94 38 }

hmWanMbus94Value10		OBJECT-TYPE
			SYNTAX	INTEGER
			MAX-ACCESS	read-only
			STATUS	current
			::= { hmWanMbus94 39 }

hmWanMbus94VIF11		OBJECT-TYPE
			SYNTAX	INTEGER
			MAX-ACCESS	read-only
			STATUS	current
			::= { hmWanMbus94 40 }

hmWanMbus94Value11		OBJECT-TYPE
			SYNTAX	INTEGER
			MAX-ACCESS	read-only
			STATUS	current
			::= { hmWanMbus94 41 }

hmWanMbus94VIF12		OBJECT-TYPE
			SYNTAX	INTEGER
			MAX-ACCESS	read-only
			STATUS	current
			::= { hmWanMbus94 42 }

hmWanMbus94Value12		OBJECT-TYPE
			SYNTAX	INTEGER
			MAX-ACCESS	read-only
			STATUS	current
			::= { hmWanMbus94 43 }

hmWanMbus94VIF13		OBJECT-TYPE
			SYNTAX	INTEGER
			MAX-ACCESS	read-only
			STATUS	current
			::= { hmWanMbus94 44 }

hmWanMbus94Value13		OBJECT-TYPE
			SYNTAX	INTEGER
			MAX-ACCESS	read-only
			STATUS	current
			::= { hmWanMbus94 45 }

hmWanMbus94VIF14		OBJECT-TYPE
			SYNTAX	INTEGER
			MAX-ACCESS	read-only
			STATUS	current
			::= { hmWanMbus94 46 }

hmWanMbus94Value14		OBJECT-TYPE
			SYNTAX	INTEGER
			MAX-ACCESS	read-only
			STATUS	current
			::= { hmWanMbus94 47 }

hmWanMbus94VIF15		OBJECT-TYPE
			SYNTAX	INTEGER
			MAX-ACCESS	read-only
			STATUS	current
			::= { hmWanMbus94 48 }

hmWanMbus94Value15		OBJECT-TYPE
			SYNTAX	INTEGER
			MAX-ACCESS	read-only
			STATUS	current
			::= { hmWanMbus94 49 }

hmWanMbus94VIF16		OBJECT-TYPE
			SYNTAX	INTEGER
			MAX-ACCESS	read-only
			STATUS	current
			::= { hmWanMbus94 50 }

hmWanMbus94Value16		OBJECT-TYPE
			SYNTAX	INTEGER
			MAX-ACCESS	read-only
			STATUS	current
			::= { hmWanMbus94 51 }

hmWanMbus94VIF17		OBJECT-TYPE
			SYNTAX	INTEGER
			MAX-ACCESS	read-only
			STATUS	current
			::= { hmWanMbus94 52 }

hmWanMbus94Value17		OBJECT-TYPE
			SYNTAX	INTEGER
			MAX-ACCESS	read-only
			STATUS	current
			::= { hmWanMbus94 53 }

hmWanMbus94VIF18		OBJECT-TYPE
			SYNTAX	INTEGER
			MAX-ACCESS	read-only
			STATUS	current
			::= { hmWanMbus94 54 }

hmWanMbus94Value18		OBJECT-TYPE
			SYNTAX	INTEGER
			MAX-ACCESS	read-only
			STATUS	current
			::= { hmWanMbus94 55 }

hmWanMbus94VIF19		OBJECT-TYPE
			SYNTAX	INTEGER
			MAX-ACCESS	read-only
			STATUS	current
			::= { hmWanMbus94 56 }

hmWanMbus94Value19		OBJECT-TYPE
			SYNTAX	INTEGER
			MAX-ACCESS	read-only
			STATUS	current
			::= { hmWanMbus94 57 }

hmWanMbus94VIF1A		OBJECT-TYPE
			SYNTAX	INTEGER
			MAX-ACCESS	read-only
			STATUS	current
			::= { hmWanMbus94 58 }

hmWanMbus94Value1A		OBJECT-TYPE
			SYNTAX	INTEGER
			MAX-ACCESS	read-only
			STATUS	current
			::= { hmWanMbus94 59 }

hmWanMbus94VIF1B		OBJECT-TYPE
			SYNTAX	INTEGER
			MAX-ACCESS	read-only
			STATUS	current
			::= { hmWanMbus94 60 }

hmWanMbus94Value1B		OBJECT-TYPE
			SYNTAX	INTEGER
			MAX-ACCESS	read-only
			STATUS	current
			::= { hmWanMbus94 61 }

hmWanMbus94VIF1C		OBJECT-TYPE
			SYNTAX	INTEGER
			MAX-ACCESS	read-only
			STATUS	current
			::= { hmWanMbus94 62 }

hmWanMbus94Value1C		OBJECT-TYPE
			SYNTAX	INTEGER
			MAX-ACCESS	read-only
			STATUS	current
			::= { hmWanMbus94 63 }

hmWanMbus94VIF1D		OBJECT-TYPE
			SYNTAX	INTEGER
			MAX-ACCESS	read-only
			STATUS	current
			::= { hmWanMbus94 64 }

hmWanMbus94Value1D		OBJECT-TYPE
			SYNTAX	INTEGER
			MAX-ACCESS	read-only
			STATUS	current
			::= { hmWanMbus94 65 }

hmWanMbus94VIF1E		OBJECT-TYPE
			SYNTAX	INTEGER
			MAX-ACCESS	read-only
			STATUS	current
			::= { hmWanMbus94 66 }

hmWanMbus94Value1E		OBJECT-TYPE
			SYNTAX	INTEGER
			MAX-ACCESS	read-only
			STATUS	current
			::= { hmWanMbus94 67 }

hmWanMbus94VIF1F		OBJECT-TYPE
			SYNTAX	INTEGER
			MAX-ACCESS	read-only
			STATUS	current
			::= { hmWanMbus94 68 }

hmWanMbus94Value1F		OBJECT-TYPE
			SYNTAX	INTEGER
			MAX-ACCESS	read-only
			STATUS	current
			::= { hmWanMbus94 69 }

hmWanMbus94VIF20		OBJECT-TYPE
			SYNTAX	INTEGER
			MAX-ACCESS	read-only
			STATUS	current
			::= { hmWanMbus94 70 }

hmWanMbus94Value20		OBJECT-TYPE
			SYNTAX	INTEGER
			MAX-ACCESS	read-only
			STATUS	current
			::= { hmWanMbus94 71 }

hmWanMbus94VIF21		OBJECT-TYPE
			SYNTAX	INTEGER
			MAX-ACCESS	read-only
			STATUS	current
			::= { hmWanMbus94 72 }

hmWanMbus94Value21		OBJECT-TYPE
			SYNTAX	INTEGER
			MAX-ACCESS	read-only
			STATUS	current
			::= { hmWanMbus94 73 }

hmWanMbus94VIF22		OBJECT-TYPE
			SYNTAX	INTEGER
			MAX-ACCESS	read-only
			STATUS	current
			::= { hmWanMbus94 74 }

hmWanMbus94Value22		OBJECT-TYPE
			SYNTAX	INTEGER
			MAX-ACCESS	read-only
			STATUS	current
			::= { hmWanMbus94 75 }

hmWanMbus94VIF23		OBJECT-TYPE
			SYNTAX	INTEGER
			MAX-ACCESS	read-only
			STATUS	current
			::= { hmWanMbus94 76 }

hmWanMbus94Value23		OBJECT-TYPE
			SYNTAX	INTEGER
			MAX-ACCESS	read-only
			STATUS	current
			::= { hmWanMbus94 77 }

hmWanMbus94VIF24		OBJECT-TYPE
			SYNTAX	INTEGER
			MAX-ACCESS	read-only
			STATUS	current
			::= { hmWanMbus94 78 }

hmWanMbus94Value24		OBJECT-TYPE
			SYNTAX	INTEGER
			MAX-ACCESS	read-only
			STATUS	current
			::= { hmWanMbus94 79 }

hmWanMbus94VIF25		OBJECT-TYPE
			SYNTAX	INTEGER
			MAX-ACCESS	read-only
			STATUS	current
			::= { hmWanMbus94 80 }

hmWanMbus94Value25		OBJECT-TYPE
			SYNTAX	INTEGER
			MAX-ACCESS	read-only
			STATUS	current
			::= { hmWanMbus94 81 }

hmWanMbus94VIF26		OBJECT-TYPE
			SYNTAX	INTEGER
			MAX-ACCESS	read-only
			STATUS	current
			::= { hmWanMbus94 82 }

hmWanMbus94Value26		OBJECT-TYPE
			SYNTAX	INTEGER
			MAX-ACCESS	read-only
			STATUS	current
			::= { hmWanMbus94 83 }

hmWanMbus94VIF27		OBJECT-TYPE
			SYNTAX	INTEGER
			MAX-ACCESS	read-only
			STATUS	current
			::= { hmWanMbus94 84 }

hmWanMbus94Value27		OBJECT-TYPE
			SYNTAX	INTEGER
			MAX-ACCESS	read-only
			STATUS	current
			::= { hmWanMbus94 85 }

hmWanMbus94VIF28		OBJECT-TYPE
			SYNTAX	INTEGER
			MAX-ACCESS	read-only
			STATUS	current
			::= { hmWanMbus94 86 }

hmWanMbus94Value28		OBJECT-TYPE
			SYNTAX	INTEGER
			MAX-ACCESS	read-only
			STATUS	current
			::= { hmWanMbus94 87 }

hmWanMbus94VIF29		OBJECT-TYPE
			SYNTAX	INTEGER
			MAX-ACCESS	read-only
			STATUS	current
			::= { hmWanMbus94 88 }

hmWanMbus94Value29		OBJECT-TYPE
			SYNTAX	INTEGER
			MAX-ACCESS	read-only
			STATUS	current
			::= { hmWanMbus94 89 }

hmWanMbus94VIF2A		OBJECT-TYPE
			SYNTAX	INTEGER
			MAX-ACCESS	read-only
			STATUS	current
			::= { hmWanMbus94 90 }

hmWanMbus94Value2A		OBJECT-TYPE
			SYNTAX	INTEGER
			MAX-ACCESS	read-only
			STATUS	current
			::= { hmWanMbus94 91 }

hmWanMbus94VIF2B		OBJECT-TYPE
			SYNTAX	INTEGER
			MAX-ACCESS	read-only
			STATUS	current
			::= { hmWanMbus94 92 }

hmWanMbus94Value2B		OBJECT-TYPE
			SYNTAX	INTEGER
			MAX-ACCESS	read-only
			STATUS	current
			::= { hmWanMbus94 93 }

hmWanMbus94VIF2C		OBJECT-TYPE
			SYNTAX	INTEGER
			MAX-ACCESS	read-only
			STATUS	current
			::= { hmWanMbus94 94 }

hmWanMbus94Value2C		OBJECT-TYPE
			SYNTAX	INTEGER
			MAX-ACCESS	read-only
			STATUS	current
			::= { hmWanMbus94 95 }

hmWanMbus94VIF2D		OBJECT-TYPE
			SYNTAX	INTEGER
			MAX-ACCESS	read-only
			STATUS	current
			::= { hmWanMbus94 96 }

hmWanMbus94Value2D		OBJECT-TYPE
			SYNTAX	INTEGER
			MAX-ACCESS	read-only
			STATUS	current
			::= { hmWanMbus94 97 }

hmWanMbus94VIF2E		OBJECT-TYPE
			SYNTAX	INTEGER
			MAX-ACCESS	read-only
			STATUS	current
			::= { hmWanMbus94 98 }

hmWanMbus94Value2E		OBJECT-TYPE
			SYNTAX	INTEGER
			MAX-ACCESS	read-only
			STATUS	current
			::= { hmWanMbus94 99 }

hmWanMbus94VIF2F		OBJECT-TYPE
			SYNTAX	INTEGER
			MAX-ACCESS	read-only
			STATUS	current
			::= { hmWanMbus94 100 }

hmWanMbus94Value2F		OBJECT-TYPE
			SYNTAX	INTEGER
			MAX-ACCESS	read-only
			STATUS	current
			::= { hmWanMbus94 101 }

hmWanMbus95			OBJECT IDENTIFIER ::= { hmWanMbus 149 }

hmWanMbus95IdNumber		OBJECT-TYPE
			SYNTAX	Gauge32
			MAX-ACCESS	read-only
			STATUS	current
			::= { hmWanMbus95 1 }

hmWanMbus95Manufacturer	OBJECT-TYPE
			SYNTAX	Gauge32
			MAX-ACCESS	read-only
			STATUS	current
			::= { hmWanMbus95 2 }

hmWanMbus95Version		OBJECT-TYPE
			SYNTAX	Gauge32
			MAX-ACCESS	read-only
			STATUS	current
			::= { hmWanMbus95 3 }

hmWanMbus95Medium		OBJECT-TYPE
			SYNTAX	Gauge32
			MAX-ACCESS	read-only
			STATUS	current
			::= { hmWanMbus95 4 }

hmWanMbus95Status		OBJECT-TYPE
			SYNTAX	Gauge32
			MAX-ACCESS	read-only
			STATUS	current
			::= { hmWanMbus95 5 }

hmWanMbus95VIF00		OBJECT-TYPE
			SYNTAX	INTEGER
			MAX-ACCESS	read-only
			STATUS	current
			::= { hmWanMbus95 6 }

hmWanMbus95Value00		OBJECT-TYPE
			SYNTAX	INTEGER
			MAX-ACCESS	read-only
			STATUS	current
			::= { hmWanMbus95 7 }

hmWanMbus95VIF01		OBJECT-TYPE
			SYNTAX	INTEGER
			MAX-ACCESS	read-only
			STATUS	current
			::= { hmWanMbus95 8 }

hmWanMbus95Value01		OBJECT-TYPE
			SYNTAX	INTEGER
			MAX-ACCESS	read-only
			STATUS	current
			::= { hmWanMbus95 9 }

hmWanMbus95VIF02		OBJECT-TYPE
			SYNTAX	INTEGER
			MAX-ACCESS	read-only
			STATUS	current
			::= { hmWanMbus95 10 }

hmWanMbus95Value02		OBJECT-TYPE
			SYNTAX	INTEGER
			MAX-ACCESS	read-only
			STATUS	current
			::= { hmWanMbus95 11 }

hmWanMbus95VIF03		OBJECT-TYPE
			SYNTAX	INTEGER
			MAX-ACCESS	read-only
			STATUS	current
			::= { hmWanMbus95 12 }

hmWanMbus95Value03		OBJECT-TYPE
			SYNTAX	INTEGER
			MAX-ACCESS	read-only
			STATUS	current
			::= { hmWanMbus95 13 }

hmWanMbus95VIF04		OBJECT-TYPE
			SYNTAX	INTEGER
			MAX-ACCESS	read-only
			STATUS	current
			::= { hmWanMbus95 14 }

hmWanMbus95Value04		OBJECT-TYPE
			SYNTAX	INTEGER
			MAX-ACCESS	read-only
			STATUS	current
			::= { hmWanMbus95 15 }

hmWanMbus95VIF05		OBJECT-TYPE
			SYNTAX	INTEGER
			MAX-ACCESS	read-only
			STATUS	current
			::= { hmWanMbus95 16 }

hmWanMbus95Value05		OBJECT-TYPE
			SYNTAX	INTEGER
			MAX-ACCESS	read-only
			STATUS	current
			::= { hmWanMbus95 17 }

hmWanMbus95VIF06		OBJECT-TYPE
			SYNTAX	INTEGER
			MAX-ACCESS	read-only
			STATUS	current
			::= { hmWanMbus95 18 }

hmWanMbus95Value06		OBJECT-TYPE
			SYNTAX	INTEGER
			MAX-ACCESS	read-only
			STATUS	current
			::= { hmWanMbus95 19 }

hmWanMbus95VIF07		OBJECT-TYPE
			SYNTAX	INTEGER
			MAX-ACCESS	read-only
			STATUS	current
			::= { hmWanMbus95 20 }

hmWanMbus95Value07		OBJECT-TYPE
			SYNTAX	INTEGER
			MAX-ACCESS	read-only
			STATUS	current
			::= { hmWanMbus95 21 }

hmWanMbus95VIF08		OBJECT-TYPE
			SYNTAX	INTEGER
			MAX-ACCESS	read-only
			STATUS	current
			::= { hmWanMbus95 22 }

hmWanMbus95Value08		OBJECT-TYPE
			SYNTAX	INTEGER
			MAX-ACCESS	read-only
			STATUS	current
			::= { hmWanMbus95 23 }

hmWanMbus95VIF09		OBJECT-TYPE
			SYNTAX	INTEGER
			MAX-ACCESS	read-only
			STATUS	current
			::= { hmWanMbus95 24 }

hmWanMbus95Value09		OBJECT-TYPE
			SYNTAX	INTEGER
			MAX-ACCESS	read-only
			STATUS	current
			::= { hmWanMbus95 25 }

hmWanMbus95VIF0A		OBJECT-TYPE
			SYNTAX	INTEGER
			MAX-ACCESS	read-only
			STATUS	current
			::= { hmWanMbus95 26 }

hmWanMbus95Value0A		OBJECT-TYPE
			SYNTAX	INTEGER
			MAX-ACCESS	read-only
			STATUS	current
			::= { hmWanMbus95 27 }

hmWanMbus95VIF0B		OBJECT-TYPE
			SYNTAX	INTEGER
			MAX-ACCESS	read-only
			STATUS	current
			::= { hmWanMbus95 28 }

hmWanMbus95Value0B		OBJECT-TYPE
			SYNTAX	INTEGER
			MAX-ACCESS	read-only
			STATUS	current
			::= { hmWanMbus95 29 }

hmWanMbus95VIF0C		OBJECT-TYPE
			SYNTAX	INTEGER
			MAX-ACCESS	read-only
			STATUS	current
			::= { hmWanMbus95 30 }

hmWanMbus95Value0C		OBJECT-TYPE
			SYNTAX	INTEGER
			MAX-ACCESS	read-only
			STATUS	current
			::= { hmWanMbus95 31 }

hmWanMbus95VIF0D		OBJECT-TYPE
			SYNTAX	INTEGER
			MAX-ACCESS	read-only
			STATUS	current
			::= { hmWanMbus95 32 }

hmWanMbus95Value0D		OBJECT-TYPE
			SYNTAX	INTEGER
			MAX-ACCESS	read-only
			STATUS	current
			::= { hmWanMbus95 33 }

hmWanMbus95VIF0E		OBJECT-TYPE
			SYNTAX	INTEGER
			MAX-ACCESS	read-only
			STATUS	current
			::= { hmWanMbus95 34 }

hmWanMbus95Value0E		OBJECT-TYPE
			SYNTAX	INTEGER
			MAX-ACCESS	read-only
			STATUS	current
			::= { hmWanMbus95 35 }

hmWanMbus95VIF0F		OBJECT-TYPE
			SYNTAX	INTEGER
			MAX-ACCESS	read-only
			STATUS	current
			::= { hmWanMbus95 36 }

hmWanMbus95Value0F		OBJECT-TYPE
			SYNTAX	INTEGER
			MAX-ACCESS	read-only
			STATUS	current
			::= { hmWanMbus95 37 }

hmWanMbus95VIF10		OBJECT-TYPE
			SYNTAX	INTEGER
			MAX-ACCESS	read-only
			STATUS	current
			::= { hmWanMbus95 38 }

hmWanMbus95Value10		OBJECT-TYPE
			SYNTAX	INTEGER
			MAX-ACCESS	read-only
			STATUS	current
			::= { hmWanMbus95 39 }

hmWanMbus95VIF11		OBJECT-TYPE
			SYNTAX	INTEGER
			MAX-ACCESS	read-only
			STATUS	current
			::= { hmWanMbus95 40 }

hmWanMbus95Value11		OBJECT-TYPE
			SYNTAX	INTEGER
			MAX-ACCESS	read-only
			STATUS	current
			::= { hmWanMbus95 41 }

hmWanMbus95VIF12		OBJECT-TYPE
			SYNTAX	INTEGER
			MAX-ACCESS	read-only
			STATUS	current
			::= { hmWanMbus95 42 }

hmWanMbus95Value12		OBJECT-TYPE
			SYNTAX	INTEGER
			MAX-ACCESS	read-only
			STATUS	current
			::= { hmWanMbus95 43 }

hmWanMbus95VIF13		OBJECT-TYPE
			SYNTAX	INTEGER
			MAX-ACCESS	read-only
			STATUS	current
			::= { hmWanMbus95 44 }

hmWanMbus95Value13		OBJECT-TYPE
			SYNTAX	INTEGER
			MAX-ACCESS	read-only
			STATUS	current
			::= { hmWanMbus95 45 }

hmWanMbus95VIF14		OBJECT-TYPE
			SYNTAX	INTEGER
			MAX-ACCESS	read-only
			STATUS	current
			::= { hmWanMbus95 46 }

hmWanMbus95Value14		OBJECT-TYPE
			SYNTAX	INTEGER
			MAX-ACCESS	read-only
			STATUS	current
			::= { hmWanMbus95 47 }

hmWanMbus95VIF15		OBJECT-TYPE
			SYNTAX	INTEGER
			MAX-ACCESS	read-only
			STATUS	current
			::= { hmWanMbus95 48 }

hmWanMbus95Value15		OBJECT-TYPE
			SYNTAX	INTEGER
			MAX-ACCESS	read-only
			STATUS	current
			::= { hmWanMbus95 49 }

hmWanMbus95VIF16		OBJECT-TYPE
			SYNTAX	INTEGER
			MAX-ACCESS	read-only
			STATUS	current
			::= { hmWanMbus95 50 }

hmWanMbus95Value16		OBJECT-TYPE
			SYNTAX	INTEGER
			MAX-ACCESS	read-only
			STATUS	current
			::= { hmWanMbus95 51 }

hmWanMbus95VIF17		OBJECT-TYPE
			SYNTAX	INTEGER
			MAX-ACCESS	read-only
			STATUS	current
			::= { hmWanMbus95 52 }

hmWanMbus95Value17		OBJECT-TYPE
			SYNTAX	INTEGER
			MAX-ACCESS	read-only
			STATUS	current
			::= { hmWanMbus95 53 }

hmWanMbus95VIF18		OBJECT-TYPE
			SYNTAX	INTEGER
			MAX-ACCESS	read-only
			STATUS	current
			::= { hmWanMbus95 54 }

hmWanMbus95Value18		OBJECT-TYPE
			SYNTAX	INTEGER
			MAX-ACCESS	read-only
			STATUS	current
			::= { hmWanMbus95 55 }

hmWanMbus95VIF19		OBJECT-TYPE
			SYNTAX	INTEGER
			MAX-ACCESS	read-only
			STATUS	current
			::= { hmWanMbus95 56 }

hmWanMbus95Value19		OBJECT-TYPE
			SYNTAX	INTEGER
			MAX-ACCESS	read-only
			STATUS	current
			::= { hmWanMbus95 57 }

hmWanMbus95VIF1A		OBJECT-TYPE
			SYNTAX	INTEGER
			MAX-ACCESS	read-only
			STATUS	current
			::= { hmWanMbus95 58 }

hmWanMbus95Value1A		OBJECT-TYPE
			SYNTAX	INTEGER
			MAX-ACCESS	read-only
			STATUS	current
			::= { hmWanMbus95 59 }

hmWanMbus95VIF1B		OBJECT-TYPE
			SYNTAX	INTEGER
			MAX-ACCESS	read-only
			STATUS	current
			::= { hmWanMbus95 60 }

hmWanMbus95Value1B		OBJECT-TYPE
			SYNTAX	INTEGER
			MAX-ACCESS	read-only
			STATUS	current
			::= { hmWanMbus95 61 }

hmWanMbus95VIF1C		OBJECT-TYPE
			SYNTAX	INTEGER
			MAX-ACCESS	read-only
			STATUS	current
			::= { hmWanMbus95 62 }

hmWanMbus95Value1C		OBJECT-TYPE
			SYNTAX	INTEGER
			MAX-ACCESS	read-only
			STATUS	current
			::= { hmWanMbus95 63 }

hmWanMbus95VIF1D		OBJECT-TYPE
			SYNTAX	INTEGER
			MAX-ACCESS	read-only
			STATUS	current
			::= { hmWanMbus95 64 }

hmWanMbus95Value1D		OBJECT-TYPE
			SYNTAX	INTEGER
			MAX-ACCESS	read-only
			STATUS	current
			::= { hmWanMbus95 65 }

hmWanMbus95VIF1E		OBJECT-TYPE
			SYNTAX	INTEGER
			MAX-ACCESS	read-only
			STATUS	current
			::= { hmWanMbus95 66 }

hmWanMbus95Value1E		OBJECT-TYPE
			SYNTAX	INTEGER
			MAX-ACCESS	read-only
			STATUS	current
			::= { hmWanMbus95 67 }

hmWanMbus95VIF1F		OBJECT-TYPE
			SYNTAX	INTEGER
			MAX-ACCESS	read-only
			STATUS	current
			::= { hmWanMbus95 68 }

hmWanMbus95Value1F		OBJECT-TYPE
			SYNTAX	INTEGER
			MAX-ACCESS	read-only
			STATUS	current
			::= { hmWanMbus95 69 }

hmWanMbus95VIF20		OBJECT-TYPE
			SYNTAX	INTEGER
			MAX-ACCESS	read-only
			STATUS	current
			::= { hmWanMbus95 70 }

hmWanMbus95Value20		OBJECT-TYPE
			SYNTAX	INTEGER
			MAX-ACCESS	read-only
			STATUS	current
			::= { hmWanMbus95 71 }

hmWanMbus95VIF21		OBJECT-TYPE
			SYNTAX	INTEGER
			MAX-ACCESS	read-only
			STATUS	current
			::= { hmWanMbus95 72 }

hmWanMbus95Value21		OBJECT-TYPE
			SYNTAX	INTEGER
			MAX-ACCESS	read-only
			STATUS	current
			::= { hmWanMbus95 73 }

hmWanMbus95VIF22		OBJECT-TYPE
			SYNTAX	INTEGER
			MAX-ACCESS	read-only
			STATUS	current
			::= { hmWanMbus95 74 }

hmWanMbus95Value22		OBJECT-TYPE
			SYNTAX	INTEGER
			MAX-ACCESS	read-only
			STATUS	current
			::= { hmWanMbus95 75 }

hmWanMbus95VIF23		OBJECT-TYPE
			SYNTAX	INTEGER
			MAX-ACCESS	read-only
			STATUS	current
			::= { hmWanMbus95 76 }

hmWanMbus95Value23		OBJECT-TYPE
			SYNTAX	INTEGER
			MAX-ACCESS	read-only
			STATUS	current
			::= { hmWanMbus95 77 }

hmWanMbus95VIF24		OBJECT-TYPE
			SYNTAX	INTEGER
			MAX-ACCESS	read-only
			STATUS	current
			::= { hmWanMbus95 78 }

hmWanMbus95Value24		OBJECT-TYPE
			SYNTAX	INTEGER
			MAX-ACCESS	read-only
			STATUS	current
			::= { hmWanMbus95 79 }

hmWanMbus95VIF25		OBJECT-TYPE
			SYNTAX	INTEGER
			MAX-ACCESS	read-only
			STATUS	current
			::= { hmWanMbus95 80 }

hmWanMbus95Value25		OBJECT-TYPE
			SYNTAX	INTEGER
			MAX-ACCESS	read-only
			STATUS	current
			::= { hmWanMbus95 81 }

hmWanMbus95VIF26		OBJECT-TYPE
			SYNTAX	INTEGER
			MAX-ACCESS	read-only
			STATUS	current
			::= { hmWanMbus95 82 }

hmWanMbus95Value26		OBJECT-TYPE
			SYNTAX	INTEGER
			MAX-ACCESS	read-only
			STATUS	current
			::= { hmWanMbus95 83 }

hmWanMbus95VIF27		OBJECT-TYPE
			SYNTAX	INTEGER
			MAX-ACCESS	read-only
			STATUS	current
			::= { hmWanMbus95 84 }

hmWanMbus95Value27		OBJECT-TYPE
			SYNTAX	INTEGER
			MAX-ACCESS	read-only
			STATUS	current
			::= { hmWanMbus95 85 }

hmWanMbus95VIF28		OBJECT-TYPE
			SYNTAX	INTEGER
			MAX-ACCESS	read-only
			STATUS	current
			::= { hmWanMbus95 86 }

hmWanMbus95Value28		OBJECT-TYPE
			SYNTAX	INTEGER
			MAX-ACCESS	read-only
			STATUS	current
			::= { hmWanMbus95 87 }

hmWanMbus95VIF29		OBJECT-TYPE
			SYNTAX	INTEGER
			MAX-ACCESS	read-only
			STATUS	current
			::= { hmWanMbus95 88 }

hmWanMbus95Value29		OBJECT-TYPE
			SYNTAX	INTEGER
			MAX-ACCESS	read-only
			STATUS	current
			::= { hmWanMbus95 89 }

hmWanMbus95VIF2A		OBJECT-TYPE
			SYNTAX	INTEGER
			MAX-ACCESS	read-only
			STATUS	current
			::= { hmWanMbus95 90 }

hmWanMbus95Value2A		OBJECT-TYPE
			SYNTAX	INTEGER
			MAX-ACCESS	read-only
			STATUS	current
			::= { hmWanMbus95 91 }

hmWanMbus95VIF2B		OBJECT-TYPE
			SYNTAX	INTEGER
			MAX-ACCESS	read-only
			STATUS	current
			::= { hmWanMbus95 92 }

hmWanMbus95Value2B		OBJECT-TYPE
			SYNTAX	INTEGER
			MAX-ACCESS	read-only
			STATUS	current
			::= { hmWanMbus95 93 }

hmWanMbus95VIF2C		OBJECT-TYPE
			SYNTAX	INTEGER
			MAX-ACCESS	read-only
			STATUS	current
			::= { hmWanMbus95 94 }

hmWanMbus95Value2C		OBJECT-TYPE
			SYNTAX	INTEGER
			MAX-ACCESS	read-only
			STATUS	current
			::= { hmWanMbus95 95 }

hmWanMbus95VIF2D		OBJECT-TYPE
			SYNTAX	INTEGER
			MAX-ACCESS	read-only
			STATUS	current
			::= { hmWanMbus95 96 }

hmWanMbus95Value2D		OBJECT-TYPE
			SYNTAX	INTEGER
			MAX-ACCESS	read-only
			STATUS	current
			::= { hmWanMbus95 97 }

hmWanMbus95VIF2E		OBJECT-TYPE
			SYNTAX	INTEGER
			MAX-ACCESS	read-only
			STATUS	current
			::= { hmWanMbus95 98 }

hmWanMbus95Value2E		OBJECT-TYPE
			SYNTAX	INTEGER
			MAX-ACCESS	read-only
			STATUS	current
			::= { hmWanMbus95 99 }

hmWanMbus95VIF2F		OBJECT-TYPE
			SYNTAX	INTEGER
			MAX-ACCESS	read-only
			STATUS	current
			::= { hmWanMbus95 100 }

hmWanMbus95Value2F		OBJECT-TYPE
			SYNTAX	INTEGER
			MAX-ACCESS	read-only
			STATUS	current
			::= { hmWanMbus95 101 }

hmWanMbus96			OBJECT IDENTIFIER ::= { hmWanMbus 150 }

hmWanMbus96IdNumber		OBJECT-TYPE
			SYNTAX	Gauge32
			MAX-ACCESS	read-only
			STATUS	current
			::= { hmWanMbus96 1 }

hmWanMbus96Manufacturer	OBJECT-TYPE
			SYNTAX	Gauge32
			MAX-ACCESS	read-only
			STATUS	current
			::= { hmWanMbus96 2 }

hmWanMbus96Version		OBJECT-TYPE
			SYNTAX	Gauge32
			MAX-ACCESS	read-only
			STATUS	current
			::= { hmWanMbus96 3 }

hmWanMbus96Medium		OBJECT-TYPE
			SYNTAX	Gauge32
			MAX-ACCESS	read-only
			STATUS	current
			::= { hmWanMbus96 4 }

hmWanMbus96Status		OBJECT-TYPE
			SYNTAX	Gauge32
			MAX-ACCESS	read-only
			STATUS	current
			::= { hmWanMbus96 5 }

hmWanMbus96VIF00		OBJECT-TYPE
			SYNTAX	INTEGER
			MAX-ACCESS	read-only
			STATUS	current
			::= { hmWanMbus96 6 }

hmWanMbus96Value00		OBJECT-TYPE
			SYNTAX	INTEGER
			MAX-ACCESS	read-only
			STATUS	current
			::= { hmWanMbus96 7 }

hmWanMbus96VIF01		OBJECT-TYPE
			SYNTAX	INTEGER
			MAX-ACCESS	read-only
			STATUS	current
			::= { hmWanMbus96 8 }

hmWanMbus96Value01		OBJECT-TYPE
			SYNTAX	INTEGER
			MAX-ACCESS	read-only
			STATUS	current
			::= { hmWanMbus96 9 }

hmWanMbus96VIF02		OBJECT-TYPE
			SYNTAX	INTEGER
			MAX-ACCESS	read-only
			STATUS	current
			::= { hmWanMbus96 10 }

hmWanMbus96Value02		OBJECT-TYPE
			SYNTAX	INTEGER
			MAX-ACCESS	read-only
			STATUS	current
			::= { hmWanMbus96 11 }

hmWanMbus96VIF03		OBJECT-TYPE
			SYNTAX	INTEGER
			MAX-ACCESS	read-only
			STATUS	current
			::= { hmWanMbus96 12 }

hmWanMbus96Value03		OBJECT-TYPE
			SYNTAX	INTEGER
			MAX-ACCESS	read-only
			STATUS	current
			::= { hmWanMbus96 13 }

hmWanMbus96VIF04		OBJECT-TYPE
			SYNTAX	INTEGER
			MAX-ACCESS	read-only
			STATUS	current
			::= { hmWanMbus96 14 }

hmWanMbus96Value04		OBJECT-TYPE
			SYNTAX	INTEGER
			MAX-ACCESS	read-only
			STATUS	current
			::= { hmWanMbus96 15 }

hmWanMbus96VIF05		OBJECT-TYPE
			SYNTAX	INTEGER
			MAX-ACCESS	read-only
			STATUS	current
			::= { hmWanMbus96 16 }

hmWanMbus96Value05		OBJECT-TYPE
			SYNTAX	INTEGER
			MAX-ACCESS	read-only
			STATUS	current
			::= { hmWanMbus96 17 }

hmWanMbus96VIF06		OBJECT-TYPE
			SYNTAX	INTEGER
			MAX-ACCESS	read-only
			STATUS	current
			::= { hmWanMbus96 18 }

hmWanMbus96Value06		OBJECT-TYPE
			SYNTAX	INTEGER
			MAX-ACCESS	read-only
			STATUS	current
			::= { hmWanMbus96 19 }

hmWanMbus96VIF07		OBJECT-TYPE
			SYNTAX	INTEGER
			MAX-ACCESS	read-only
			STATUS	current
			::= { hmWanMbus96 20 }

hmWanMbus96Value07		OBJECT-TYPE
			SYNTAX	INTEGER
			MAX-ACCESS	read-only
			STATUS	current
			::= { hmWanMbus96 21 }

hmWanMbus96VIF08		OBJECT-TYPE
			SYNTAX	INTEGER
			MAX-ACCESS	read-only
			STATUS	current
			::= { hmWanMbus96 22 }

hmWanMbus96Value08		OBJECT-TYPE
			SYNTAX	INTEGER
			MAX-ACCESS	read-only
			STATUS	current
			::= { hmWanMbus96 23 }

hmWanMbus96VIF09		OBJECT-TYPE
			SYNTAX	INTEGER
			MAX-ACCESS	read-only
			STATUS	current
			::= { hmWanMbus96 24 }

hmWanMbus96Value09		OBJECT-TYPE
			SYNTAX	INTEGER
			MAX-ACCESS	read-only
			STATUS	current
			::= { hmWanMbus96 25 }

hmWanMbus96VIF0A		OBJECT-TYPE
			SYNTAX	INTEGER
			MAX-ACCESS	read-only
			STATUS	current
			::= { hmWanMbus96 26 }

hmWanMbus96Value0A		OBJECT-TYPE
			SYNTAX	INTEGER
			MAX-ACCESS	read-only
			STATUS	current
			::= { hmWanMbus96 27 }

hmWanMbus96VIF0B		OBJECT-TYPE
			SYNTAX	INTEGER
			MAX-ACCESS	read-only
			STATUS	current
			::= { hmWanMbus96 28 }

hmWanMbus96Value0B		OBJECT-TYPE
			SYNTAX	INTEGER
			MAX-ACCESS	read-only
			STATUS	current
			::= { hmWanMbus96 29 }

hmWanMbus96VIF0C		OBJECT-TYPE
			SYNTAX	INTEGER
			MAX-ACCESS	read-only
			STATUS	current
			::= { hmWanMbus96 30 }

hmWanMbus96Value0C		OBJECT-TYPE
			SYNTAX	INTEGER
			MAX-ACCESS	read-only
			STATUS	current
			::= { hmWanMbus96 31 }

hmWanMbus96VIF0D		OBJECT-TYPE
			SYNTAX	INTEGER
			MAX-ACCESS	read-only
			STATUS	current
			::= { hmWanMbus96 32 }

hmWanMbus96Value0D		OBJECT-TYPE
			SYNTAX	INTEGER
			MAX-ACCESS	read-only
			STATUS	current
			::= { hmWanMbus96 33 }

hmWanMbus96VIF0E		OBJECT-TYPE
			SYNTAX	INTEGER
			MAX-ACCESS	read-only
			STATUS	current
			::= { hmWanMbus96 34 }

hmWanMbus96Value0E		OBJECT-TYPE
			SYNTAX	INTEGER
			MAX-ACCESS	read-only
			STATUS	current
			::= { hmWanMbus96 35 }

hmWanMbus96VIF0F		OBJECT-TYPE
			SYNTAX	INTEGER
			MAX-ACCESS	read-only
			STATUS	current
			::= { hmWanMbus96 36 }

hmWanMbus96Value0F		OBJECT-TYPE
			SYNTAX	INTEGER
			MAX-ACCESS	read-only
			STATUS	current
			::= { hmWanMbus96 37 }

hmWanMbus96VIF10		OBJECT-TYPE
			SYNTAX	INTEGER
			MAX-ACCESS	read-only
			STATUS	current
			::= { hmWanMbus96 38 }

hmWanMbus96Value10		OBJECT-TYPE
			SYNTAX	INTEGER
			MAX-ACCESS	read-only
			STATUS	current
			::= { hmWanMbus96 39 }

hmWanMbus96VIF11		OBJECT-TYPE
			SYNTAX	INTEGER
			MAX-ACCESS	read-only
			STATUS	current
			::= { hmWanMbus96 40 }

hmWanMbus96Value11		OBJECT-TYPE
			SYNTAX	INTEGER
			MAX-ACCESS	read-only
			STATUS	current
			::= { hmWanMbus96 41 }

hmWanMbus96VIF12		OBJECT-TYPE
			SYNTAX	INTEGER
			MAX-ACCESS	read-only
			STATUS	current
			::= { hmWanMbus96 42 }

hmWanMbus96Value12		OBJECT-TYPE
			SYNTAX	INTEGER
			MAX-ACCESS	read-only
			STATUS	current
			::= { hmWanMbus96 43 }

hmWanMbus96VIF13		OBJECT-TYPE
			SYNTAX	INTEGER
			MAX-ACCESS	read-only
			STATUS	current
			::= { hmWanMbus96 44 }

hmWanMbus96Value13		OBJECT-TYPE
			SYNTAX	INTEGER
			MAX-ACCESS	read-only
			STATUS	current
			::= { hmWanMbus96 45 }

hmWanMbus96VIF14		OBJECT-TYPE
			SYNTAX	INTEGER
			MAX-ACCESS	read-only
			STATUS	current
			::= { hmWanMbus96 46 }

hmWanMbus96Value14		OBJECT-TYPE
			SYNTAX	INTEGER
			MAX-ACCESS	read-only
			STATUS	current
			::= { hmWanMbus96 47 }

hmWanMbus96VIF15		OBJECT-TYPE
			SYNTAX	INTEGER
			MAX-ACCESS	read-only
			STATUS	current
			::= { hmWanMbus96 48 }

hmWanMbus96Value15		OBJECT-TYPE
			SYNTAX	INTEGER
			MAX-ACCESS	read-only
			STATUS	current
			::= { hmWanMbus96 49 }

hmWanMbus96VIF16		OBJECT-TYPE
			SYNTAX	INTEGER
			MAX-ACCESS	read-only
			STATUS	current
			::= { hmWanMbus96 50 }

hmWanMbus96Value16		OBJECT-TYPE
			SYNTAX	INTEGER
			MAX-ACCESS	read-only
			STATUS	current
			::= { hmWanMbus96 51 }

hmWanMbus96VIF17		OBJECT-TYPE
			SYNTAX	INTEGER
			MAX-ACCESS	read-only
			STATUS	current
			::= { hmWanMbus96 52 }

hmWanMbus96Value17		OBJECT-TYPE
			SYNTAX	INTEGER
			MAX-ACCESS	read-only
			STATUS	current
			::= { hmWanMbus96 53 }

hmWanMbus96VIF18		OBJECT-TYPE
			SYNTAX	INTEGER
			MAX-ACCESS	read-only
			STATUS	current
			::= { hmWanMbus96 54 }

hmWanMbus96Value18		OBJECT-TYPE
			SYNTAX	INTEGER
			MAX-ACCESS	read-only
			STATUS	current
			::= { hmWanMbus96 55 }

hmWanMbus96VIF19		OBJECT-TYPE
			SYNTAX	INTEGER
			MAX-ACCESS	read-only
			STATUS	current
			::= { hmWanMbus96 56 }

hmWanMbus96Value19		OBJECT-TYPE
			SYNTAX	INTEGER
			MAX-ACCESS	read-only
			STATUS	current
			::= { hmWanMbus96 57 }

hmWanMbus96VIF1A		OBJECT-TYPE
			SYNTAX	INTEGER
			MAX-ACCESS	read-only
			STATUS	current
			::= { hmWanMbus96 58 }

hmWanMbus96Value1A		OBJECT-TYPE
			SYNTAX	INTEGER
			MAX-ACCESS	read-only
			STATUS	current
			::= { hmWanMbus96 59 }

hmWanMbus96VIF1B		OBJECT-TYPE
			SYNTAX	INTEGER
			MAX-ACCESS	read-only
			STATUS	current
			::= { hmWanMbus96 60 }

hmWanMbus96Value1B		OBJECT-TYPE
			SYNTAX	INTEGER
			MAX-ACCESS	read-only
			STATUS	current
			::= { hmWanMbus96 61 }

hmWanMbus96VIF1C		OBJECT-TYPE
			SYNTAX	INTEGER
			MAX-ACCESS	read-only
			STATUS	current
			::= { hmWanMbus96 62 }

hmWanMbus96Value1C		OBJECT-TYPE
			SYNTAX	INTEGER
			MAX-ACCESS	read-only
			STATUS	current
			::= { hmWanMbus96 63 }

hmWanMbus96VIF1D		OBJECT-TYPE
			SYNTAX	INTEGER
			MAX-ACCESS	read-only
			STATUS	current
			::= { hmWanMbus96 64 }

hmWanMbus96Value1D		OBJECT-TYPE
			SYNTAX	INTEGER
			MAX-ACCESS	read-only
			STATUS	current
			::= { hmWanMbus96 65 }

hmWanMbus96VIF1E		OBJECT-TYPE
			SYNTAX	INTEGER
			MAX-ACCESS	read-only
			STATUS	current
			::= { hmWanMbus96 66 }

hmWanMbus96Value1E		OBJECT-TYPE
			SYNTAX	INTEGER
			MAX-ACCESS	read-only
			STATUS	current
			::= { hmWanMbus96 67 }

hmWanMbus96VIF1F		OBJECT-TYPE
			SYNTAX	INTEGER
			MAX-ACCESS	read-only
			STATUS	current
			::= { hmWanMbus96 68 }

hmWanMbus96Value1F		OBJECT-TYPE
			SYNTAX	INTEGER
			MAX-ACCESS	read-only
			STATUS	current
			::= { hmWanMbus96 69 }

hmWanMbus96VIF20		OBJECT-TYPE
			SYNTAX	INTEGER
			MAX-ACCESS	read-only
			STATUS	current
			::= { hmWanMbus96 70 }

hmWanMbus96Value20		OBJECT-TYPE
			SYNTAX	INTEGER
			MAX-ACCESS	read-only
			STATUS	current
			::= { hmWanMbus96 71 }

hmWanMbus96VIF21		OBJECT-TYPE
			SYNTAX	INTEGER
			MAX-ACCESS	read-only
			STATUS	current
			::= { hmWanMbus96 72 }

hmWanMbus96Value21		OBJECT-TYPE
			SYNTAX	INTEGER
			MAX-ACCESS	read-only
			STATUS	current
			::= { hmWanMbus96 73 }

hmWanMbus96VIF22		OBJECT-TYPE
			SYNTAX	INTEGER
			MAX-ACCESS	read-only
			STATUS	current
			::= { hmWanMbus96 74 }

hmWanMbus96Value22		OBJECT-TYPE
			SYNTAX	INTEGER
			MAX-ACCESS	read-only
			STATUS	current
			::= { hmWanMbus96 75 }

hmWanMbus96VIF23		OBJECT-TYPE
			SYNTAX	INTEGER
			MAX-ACCESS	read-only
			STATUS	current
			::= { hmWanMbus96 76 }

hmWanMbus96Value23		OBJECT-TYPE
			SYNTAX	INTEGER
			MAX-ACCESS	read-only
			STATUS	current
			::= { hmWanMbus96 77 }

hmWanMbus96VIF24		OBJECT-TYPE
			SYNTAX	INTEGER
			MAX-ACCESS	read-only
			STATUS	current
			::= { hmWanMbus96 78 }

hmWanMbus96Value24		OBJECT-TYPE
			SYNTAX	INTEGER
			MAX-ACCESS	read-only
			STATUS	current
			::= { hmWanMbus96 79 }

hmWanMbus96VIF25		OBJECT-TYPE
			SYNTAX	INTEGER
			MAX-ACCESS	read-only
			STATUS	current
			::= { hmWanMbus96 80 }

hmWanMbus96Value25		OBJECT-TYPE
			SYNTAX	INTEGER
			MAX-ACCESS	read-only
			STATUS	current
			::= { hmWanMbus96 81 }

hmWanMbus96VIF26		OBJECT-TYPE
			SYNTAX	INTEGER
			MAX-ACCESS	read-only
			STATUS	current
			::= { hmWanMbus96 82 }

hmWanMbus96Value26		OBJECT-TYPE
			SYNTAX	INTEGER
			MAX-ACCESS	read-only
			STATUS	current
			::= { hmWanMbus96 83 }

hmWanMbus96VIF27		OBJECT-TYPE
			SYNTAX	INTEGER
			MAX-ACCESS	read-only
			STATUS	current
			::= { hmWanMbus96 84 }

hmWanMbus96Value27		OBJECT-TYPE
			SYNTAX	INTEGER
			MAX-ACCESS	read-only
			STATUS	current
			::= { hmWanMbus96 85 }

hmWanMbus96VIF28		OBJECT-TYPE
			SYNTAX	INTEGER
			MAX-ACCESS	read-only
			STATUS	current
			::= { hmWanMbus96 86 }

hmWanMbus96Value28		OBJECT-TYPE
			SYNTAX	INTEGER
			MAX-ACCESS	read-only
			STATUS	current
			::= { hmWanMbus96 87 }

hmWanMbus96VIF29		OBJECT-TYPE
			SYNTAX	INTEGER
			MAX-ACCESS	read-only
			STATUS	current
			::= { hmWanMbus96 88 }

hmWanMbus96Value29		OBJECT-TYPE
			SYNTAX	INTEGER
			MAX-ACCESS	read-only
			STATUS	current
			::= { hmWanMbus96 89 }

hmWanMbus96VIF2A		OBJECT-TYPE
			SYNTAX	INTEGER
			MAX-ACCESS	read-only
			STATUS	current
			::= { hmWanMbus96 90 }

hmWanMbus96Value2A		OBJECT-TYPE
			SYNTAX	INTEGER
			MAX-ACCESS	read-only
			STATUS	current
			::= { hmWanMbus96 91 }

hmWanMbus96VIF2B		OBJECT-TYPE
			SYNTAX	INTEGER
			MAX-ACCESS	read-only
			STATUS	current
			::= { hmWanMbus96 92 }

hmWanMbus96Value2B		OBJECT-TYPE
			SYNTAX	INTEGER
			MAX-ACCESS	read-only
			STATUS	current
			::= { hmWanMbus96 93 }

hmWanMbus96VIF2C		OBJECT-TYPE
			SYNTAX	INTEGER
			MAX-ACCESS	read-only
			STATUS	current
			::= { hmWanMbus96 94 }

hmWanMbus96Value2C		OBJECT-TYPE
			SYNTAX	INTEGER
			MAX-ACCESS	read-only
			STATUS	current
			::= { hmWanMbus96 95 }

hmWanMbus96VIF2D		OBJECT-TYPE
			SYNTAX	INTEGER
			MAX-ACCESS	read-only
			STATUS	current
			::= { hmWanMbus96 96 }

hmWanMbus96Value2D		OBJECT-TYPE
			SYNTAX	INTEGER
			MAX-ACCESS	read-only
			STATUS	current
			::= { hmWanMbus96 97 }

hmWanMbus96VIF2E		OBJECT-TYPE
			SYNTAX	INTEGER
			MAX-ACCESS	read-only
			STATUS	current
			::= { hmWanMbus96 98 }

hmWanMbus96Value2E		OBJECT-TYPE
			SYNTAX	INTEGER
			MAX-ACCESS	read-only
			STATUS	current
			::= { hmWanMbus96 99 }

hmWanMbus96VIF2F		OBJECT-TYPE
			SYNTAX	INTEGER
			MAX-ACCESS	read-only
			STATUS	current
			::= { hmWanMbus96 100 }

hmWanMbus96Value2F		OBJECT-TYPE
			SYNTAX	INTEGER
			MAX-ACCESS	read-only
			STATUS	current
			::= { hmWanMbus96 101 }

hmWanMbus97			OBJECT IDENTIFIER ::= { hmWanMbus 151 }

hmWanMbus97IdNumber		OBJECT-TYPE
			SYNTAX	Gauge32
			MAX-ACCESS	read-only
			STATUS	current
			::= { hmWanMbus97 1 }

hmWanMbus97Manufacturer	OBJECT-TYPE
			SYNTAX	Gauge32
			MAX-ACCESS	read-only
			STATUS	current
			::= { hmWanMbus97 2 }

hmWanMbus97Version		OBJECT-TYPE
			SYNTAX	Gauge32
			MAX-ACCESS	read-only
			STATUS	current
			::= { hmWanMbus97 3 }

hmWanMbus97Medium		OBJECT-TYPE
			SYNTAX	Gauge32
			MAX-ACCESS	read-only
			STATUS	current
			::= { hmWanMbus97 4 }

hmWanMbus97Status		OBJECT-TYPE
			SYNTAX	Gauge32
			MAX-ACCESS	read-only
			STATUS	current
			::= { hmWanMbus97 5 }

hmWanMbus97VIF00		OBJECT-TYPE
			SYNTAX	INTEGER
			MAX-ACCESS	read-only
			STATUS	current
			::= { hmWanMbus97 6 }

hmWanMbus97Value00		OBJECT-TYPE
			SYNTAX	INTEGER
			MAX-ACCESS	read-only
			STATUS	current
			::= { hmWanMbus97 7 }

hmWanMbus97VIF01		OBJECT-TYPE
			SYNTAX	INTEGER
			MAX-ACCESS	read-only
			STATUS	current
			::= { hmWanMbus97 8 }

hmWanMbus97Value01		OBJECT-TYPE
			SYNTAX	INTEGER
			MAX-ACCESS	read-only
			STATUS	current
			::= { hmWanMbus97 9 }

hmWanMbus97VIF02		OBJECT-TYPE
			SYNTAX	INTEGER
			MAX-ACCESS	read-only
			STATUS	current
			::= { hmWanMbus97 10 }

hmWanMbus97Value02		OBJECT-TYPE
			SYNTAX	INTEGER
			MAX-ACCESS	read-only
			STATUS	current
			::= { hmWanMbus97 11 }

hmWanMbus97VIF03		OBJECT-TYPE
			SYNTAX	INTEGER
			MAX-ACCESS	read-only
			STATUS	current
			::= { hmWanMbus97 12 }

hmWanMbus97Value03		OBJECT-TYPE
			SYNTAX	INTEGER
			MAX-ACCESS	read-only
			STATUS	current
			::= { hmWanMbus97 13 }

hmWanMbus97VIF04		OBJECT-TYPE
			SYNTAX	INTEGER
			MAX-ACCESS	read-only
			STATUS	current
			::= { hmWanMbus97 14 }

hmWanMbus97Value04		OBJECT-TYPE
			SYNTAX	INTEGER
			MAX-ACCESS	read-only
			STATUS	current
			::= { hmWanMbus97 15 }

hmWanMbus97VIF05		OBJECT-TYPE
			SYNTAX	INTEGER
			MAX-ACCESS	read-only
			STATUS	current
			::= { hmWanMbus97 16 }

hmWanMbus97Value05		OBJECT-TYPE
			SYNTAX	INTEGER
			MAX-ACCESS	read-only
			STATUS	current
			::= { hmWanMbus97 17 }

hmWanMbus97VIF06		OBJECT-TYPE
			SYNTAX	INTEGER
			MAX-ACCESS	read-only
			STATUS	current
			::= { hmWanMbus97 18 }

hmWanMbus97Value06		OBJECT-TYPE
			SYNTAX	INTEGER
			MAX-ACCESS	read-only
			STATUS	current
			::= { hmWanMbus97 19 }

hmWanMbus97VIF07		OBJECT-TYPE
			SYNTAX	INTEGER
			MAX-ACCESS	read-only
			STATUS	current
			::= { hmWanMbus97 20 }

hmWanMbus97Value07		OBJECT-TYPE
			SYNTAX	INTEGER
			MAX-ACCESS	read-only
			STATUS	current
			::= { hmWanMbus97 21 }

hmWanMbus97VIF08		OBJECT-TYPE
			SYNTAX	INTEGER
			MAX-ACCESS	read-only
			STATUS	current
			::= { hmWanMbus97 22 }

hmWanMbus97Value08		OBJECT-TYPE
			SYNTAX	INTEGER
			MAX-ACCESS	read-only
			STATUS	current
			::= { hmWanMbus97 23 }

hmWanMbus97VIF09		OBJECT-TYPE
			SYNTAX	INTEGER
			MAX-ACCESS	read-only
			STATUS	current
			::= { hmWanMbus97 24 }

hmWanMbus97Value09		OBJECT-TYPE
			SYNTAX	INTEGER
			MAX-ACCESS	read-only
			STATUS	current
			::= { hmWanMbus97 25 }

hmWanMbus97VIF0A		OBJECT-TYPE
			SYNTAX	INTEGER
			MAX-ACCESS	read-only
			STATUS	current
			::= { hmWanMbus97 26 }

hmWanMbus97Value0A		OBJECT-TYPE
			SYNTAX	INTEGER
			MAX-ACCESS	read-only
			STATUS	current
			::= { hmWanMbus97 27 }

hmWanMbus97VIF0B		OBJECT-TYPE
			SYNTAX	INTEGER
			MAX-ACCESS	read-only
			STATUS	current
			::= { hmWanMbus97 28 }

hmWanMbus97Value0B		OBJECT-TYPE
			SYNTAX	INTEGER
			MAX-ACCESS	read-only
			STATUS	current
			::= { hmWanMbus97 29 }

hmWanMbus97VIF0C		OBJECT-TYPE
			SYNTAX	INTEGER
			MAX-ACCESS	read-only
			STATUS	current
			::= { hmWanMbus97 30 }

hmWanMbus97Value0C		OBJECT-TYPE
			SYNTAX	INTEGER
			MAX-ACCESS	read-only
			STATUS	current
			::= { hmWanMbus97 31 }

hmWanMbus97VIF0D		OBJECT-TYPE
			SYNTAX	INTEGER
			MAX-ACCESS	read-only
			STATUS	current
			::= { hmWanMbus97 32 }

hmWanMbus97Value0D		OBJECT-TYPE
			SYNTAX	INTEGER
			MAX-ACCESS	read-only
			STATUS	current
			::= { hmWanMbus97 33 }

hmWanMbus97VIF0E		OBJECT-TYPE
			SYNTAX	INTEGER
			MAX-ACCESS	read-only
			STATUS	current
			::= { hmWanMbus97 34 }

hmWanMbus97Value0E		OBJECT-TYPE
			SYNTAX	INTEGER
			MAX-ACCESS	read-only
			STATUS	current
			::= { hmWanMbus97 35 }

hmWanMbus97VIF0F		OBJECT-TYPE
			SYNTAX	INTEGER
			MAX-ACCESS	read-only
			STATUS	current
			::= { hmWanMbus97 36 }

hmWanMbus97Value0F		OBJECT-TYPE
			SYNTAX	INTEGER
			MAX-ACCESS	read-only
			STATUS	current
			::= { hmWanMbus97 37 }

hmWanMbus97VIF10		OBJECT-TYPE
			SYNTAX	INTEGER
			MAX-ACCESS	read-only
			STATUS	current
			::= { hmWanMbus97 38 }

hmWanMbus97Value10		OBJECT-TYPE
			SYNTAX	INTEGER
			MAX-ACCESS	read-only
			STATUS	current
			::= { hmWanMbus97 39 }

hmWanMbus97VIF11		OBJECT-TYPE
			SYNTAX	INTEGER
			MAX-ACCESS	read-only
			STATUS	current
			::= { hmWanMbus97 40 }

hmWanMbus97Value11		OBJECT-TYPE
			SYNTAX	INTEGER
			MAX-ACCESS	read-only
			STATUS	current
			::= { hmWanMbus97 41 }

hmWanMbus97VIF12		OBJECT-TYPE
			SYNTAX	INTEGER
			MAX-ACCESS	read-only
			STATUS	current
			::= { hmWanMbus97 42 }

hmWanMbus97Value12		OBJECT-TYPE
			SYNTAX	INTEGER
			MAX-ACCESS	read-only
			STATUS	current
			::= { hmWanMbus97 43 }

hmWanMbus97VIF13		OBJECT-TYPE
			SYNTAX	INTEGER
			MAX-ACCESS	read-only
			STATUS	current
			::= { hmWanMbus97 44 }

hmWanMbus97Value13		OBJECT-TYPE
			SYNTAX	INTEGER
			MAX-ACCESS	read-only
			STATUS	current
			::= { hmWanMbus97 45 }

hmWanMbus97VIF14		OBJECT-TYPE
			SYNTAX	INTEGER
			MAX-ACCESS	read-only
			STATUS	current
			::= { hmWanMbus97 46 }

hmWanMbus97Value14		OBJECT-TYPE
			SYNTAX	INTEGER
			MAX-ACCESS	read-only
			STATUS	current
			::= { hmWanMbus97 47 }

hmWanMbus97VIF15		OBJECT-TYPE
			SYNTAX	INTEGER
			MAX-ACCESS	read-only
			STATUS	current
			::= { hmWanMbus97 48 }

hmWanMbus97Value15		OBJECT-TYPE
			SYNTAX	INTEGER
			MAX-ACCESS	read-only
			STATUS	current
			::= { hmWanMbus97 49 }

hmWanMbus97VIF16		OBJECT-TYPE
			SYNTAX	INTEGER
			MAX-ACCESS	read-only
			STATUS	current
			::= { hmWanMbus97 50 }

hmWanMbus97Value16		OBJECT-TYPE
			SYNTAX	INTEGER
			MAX-ACCESS	read-only
			STATUS	current
			::= { hmWanMbus97 51 }

hmWanMbus97VIF17		OBJECT-TYPE
			SYNTAX	INTEGER
			MAX-ACCESS	read-only
			STATUS	current
			::= { hmWanMbus97 52 }

hmWanMbus97Value17		OBJECT-TYPE
			SYNTAX	INTEGER
			MAX-ACCESS	read-only
			STATUS	current
			::= { hmWanMbus97 53 }

hmWanMbus97VIF18		OBJECT-TYPE
			SYNTAX	INTEGER
			MAX-ACCESS	read-only
			STATUS	current
			::= { hmWanMbus97 54 }

hmWanMbus97Value18		OBJECT-TYPE
			SYNTAX	INTEGER
			MAX-ACCESS	read-only
			STATUS	current
			::= { hmWanMbus97 55 }

hmWanMbus97VIF19		OBJECT-TYPE
			SYNTAX	INTEGER
			MAX-ACCESS	read-only
			STATUS	current
			::= { hmWanMbus97 56 }

hmWanMbus97Value19		OBJECT-TYPE
			SYNTAX	INTEGER
			MAX-ACCESS	read-only
			STATUS	current
			::= { hmWanMbus97 57 }

hmWanMbus97VIF1A		OBJECT-TYPE
			SYNTAX	INTEGER
			MAX-ACCESS	read-only
			STATUS	current
			::= { hmWanMbus97 58 }

hmWanMbus97Value1A		OBJECT-TYPE
			SYNTAX	INTEGER
			MAX-ACCESS	read-only
			STATUS	current
			::= { hmWanMbus97 59 }

hmWanMbus97VIF1B		OBJECT-TYPE
			SYNTAX	INTEGER
			MAX-ACCESS	read-only
			STATUS	current
			::= { hmWanMbus97 60 }

hmWanMbus97Value1B		OBJECT-TYPE
			SYNTAX	INTEGER
			MAX-ACCESS	read-only
			STATUS	current
			::= { hmWanMbus97 61 }

hmWanMbus97VIF1C		OBJECT-TYPE
			SYNTAX	INTEGER
			MAX-ACCESS	read-only
			STATUS	current
			::= { hmWanMbus97 62 }

hmWanMbus97Value1C		OBJECT-TYPE
			SYNTAX	INTEGER
			MAX-ACCESS	read-only
			STATUS	current
			::= { hmWanMbus97 63 }

hmWanMbus97VIF1D		OBJECT-TYPE
			SYNTAX	INTEGER
			MAX-ACCESS	read-only
			STATUS	current
			::= { hmWanMbus97 64 }

hmWanMbus97Value1D		OBJECT-TYPE
			SYNTAX	INTEGER
			MAX-ACCESS	read-only
			STATUS	current
			::= { hmWanMbus97 65 }

hmWanMbus97VIF1E		OBJECT-TYPE
			SYNTAX	INTEGER
			MAX-ACCESS	read-only
			STATUS	current
			::= { hmWanMbus97 66 }

hmWanMbus97Value1E		OBJECT-TYPE
			SYNTAX	INTEGER
			MAX-ACCESS	read-only
			STATUS	current
			::= { hmWanMbus97 67 }

hmWanMbus97VIF1F		OBJECT-TYPE
			SYNTAX	INTEGER
			MAX-ACCESS	read-only
			STATUS	current
			::= { hmWanMbus97 68 }

hmWanMbus97Value1F		OBJECT-TYPE
			SYNTAX	INTEGER
			MAX-ACCESS	read-only
			STATUS	current
			::= { hmWanMbus97 69 }

hmWanMbus97VIF20		OBJECT-TYPE
			SYNTAX	INTEGER
			MAX-ACCESS	read-only
			STATUS	current
			::= { hmWanMbus97 70 }

hmWanMbus97Value20		OBJECT-TYPE
			SYNTAX	INTEGER
			MAX-ACCESS	read-only
			STATUS	current
			::= { hmWanMbus97 71 }

hmWanMbus97VIF21		OBJECT-TYPE
			SYNTAX	INTEGER
			MAX-ACCESS	read-only
			STATUS	current
			::= { hmWanMbus97 72 }

hmWanMbus97Value21		OBJECT-TYPE
			SYNTAX	INTEGER
			MAX-ACCESS	read-only
			STATUS	current
			::= { hmWanMbus97 73 }

hmWanMbus97VIF22		OBJECT-TYPE
			SYNTAX	INTEGER
			MAX-ACCESS	read-only
			STATUS	current
			::= { hmWanMbus97 74 }

hmWanMbus97Value22		OBJECT-TYPE
			SYNTAX	INTEGER
			MAX-ACCESS	read-only
			STATUS	current
			::= { hmWanMbus97 75 }

hmWanMbus97VIF23		OBJECT-TYPE
			SYNTAX	INTEGER
			MAX-ACCESS	read-only
			STATUS	current
			::= { hmWanMbus97 76 }

hmWanMbus97Value23		OBJECT-TYPE
			SYNTAX	INTEGER
			MAX-ACCESS	read-only
			STATUS	current
			::= { hmWanMbus97 77 }

hmWanMbus97VIF24		OBJECT-TYPE
			SYNTAX	INTEGER
			MAX-ACCESS	read-only
			STATUS	current
			::= { hmWanMbus97 78 }

hmWanMbus97Value24		OBJECT-TYPE
			SYNTAX	INTEGER
			MAX-ACCESS	read-only
			STATUS	current
			::= { hmWanMbus97 79 }

hmWanMbus97VIF25		OBJECT-TYPE
			SYNTAX	INTEGER
			MAX-ACCESS	read-only
			STATUS	current
			::= { hmWanMbus97 80 }

hmWanMbus97Value25		OBJECT-TYPE
			SYNTAX	INTEGER
			MAX-ACCESS	read-only
			STATUS	current
			::= { hmWanMbus97 81 }

hmWanMbus97VIF26		OBJECT-TYPE
			SYNTAX	INTEGER
			MAX-ACCESS	read-only
			STATUS	current
			::= { hmWanMbus97 82 }

hmWanMbus97Value26		OBJECT-TYPE
			SYNTAX	INTEGER
			MAX-ACCESS	read-only
			STATUS	current
			::= { hmWanMbus97 83 }

hmWanMbus97VIF27		OBJECT-TYPE
			SYNTAX	INTEGER
			MAX-ACCESS	read-only
			STATUS	current
			::= { hmWanMbus97 84 }

hmWanMbus97Value27		OBJECT-TYPE
			SYNTAX	INTEGER
			MAX-ACCESS	read-only
			STATUS	current
			::= { hmWanMbus97 85 }

hmWanMbus97VIF28		OBJECT-TYPE
			SYNTAX	INTEGER
			MAX-ACCESS	read-only
			STATUS	current
			::= { hmWanMbus97 86 }

hmWanMbus97Value28		OBJECT-TYPE
			SYNTAX	INTEGER
			MAX-ACCESS	read-only
			STATUS	current
			::= { hmWanMbus97 87 }

hmWanMbus97VIF29		OBJECT-TYPE
			SYNTAX	INTEGER
			MAX-ACCESS	read-only
			STATUS	current
			::= { hmWanMbus97 88 }

hmWanMbus97Value29		OBJECT-TYPE
			SYNTAX	INTEGER
			MAX-ACCESS	read-only
			STATUS	current
			::= { hmWanMbus97 89 }

hmWanMbus97VIF2A		OBJECT-TYPE
			SYNTAX	INTEGER
			MAX-ACCESS	read-only
			STATUS	current
			::= { hmWanMbus97 90 }

hmWanMbus97Value2A		OBJECT-TYPE
			SYNTAX	INTEGER
			MAX-ACCESS	read-only
			STATUS	current
			::= { hmWanMbus97 91 }

hmWanMbus97VIF2B		OBJECT-TYPE
			SYNTAX	INTEGER
			MAX-ACCESS	read-only
			STATUS	current
			::= { hmWanMbus97 92 }

hmWanMbus97Value2B		OBJECT-TYPE
			SYNTAX	INTEGER
			MAX-ACCESS	read-only
			STATUS	current
			::= { hmWanMbus97 93 }

hmWanMbus97VIF2C		OBJECT-TYPE
			SYNTAX	INTEGER
			MAX-ACCESS	read-only
			STATUS	current
			::= { hmWanMbus97 94 }

hmWanMbus97Value2C		OBJECT-TYPE
			SYNTAX	INTEGER
			MAX-ACCESS	read-only
			STATUS	current
			::= { hmWanMbus97 95 }

hmWanMbus97VIF2D		OBJECT-TYPE
			SYNTAX	INTEGER
			MAX-ACCESS	read-only
			STATUS	current
			::= { hmWanMbus97 96 }

hmWanMbus97Value2D		OBJECT-TYPE
			SYNTAX	INTEGER
			MAX-ACCESS	read-only
			STATUS	current
			::= { hmWanMbus97 97 }

hmWanMbus97VIF2E		OBJECT-TYPE
			SYNTAX	INTEGER
			MAX-ACCESS	read-only
			STATUS	current
			::= { hmWanMbus97 98 }

hmWanMbus97Value2E		OBJECT-TYPE
			SYNTAX	INTEGER
			MAX-ACCESS	read-only
			STATUS	current
			::= { hmWanMbus97 99 }

hmWanMbus97VIF2F		OBJECT-TYPE
			SYNTAX	INTEGER
			MAX-ACCESS	read-only
			STATUS	current
			::= { hmWanMbus97 100 }

hmWanMbus97Value2F		OBJECT-TYPE
			SYNTAX	INTEGER
			MAX-ACCESS	read-only
			STATUS	current
			::= { hmWanMbus97 101 }

hmWanMbus98			OBJECT IDENTIFIER ::= { hmWanMbus 152 }

hmWanMbus98IdNumber		OBJECT-TYPE
			SYNTAX	Gauge32
			MAX-ACCESS	read-only
			STATUS	current
			::= { hmWanMbus98 1 }

hmWanMbus98Manufacturer	OBJECT-TYPE
			SYNTAX	Gauge32
			MAX-ACCESS	read-only
			STATUS	current
			::= { hmWanMbus98 2 }

hmWanMbus98Version		OBJECT-TYPE
			SYNTAX	Gauge32
			MAX-ACCESS	read-only
			STATUS	current
			::= { hmWanMbus98 3 }

hmWanMbus98Medium		OBJECT-TYPE
			SYNTAX	Gauge32
			MAX-ACCESS	read-only
			STATUS	current
			::= { hmWanMbus98 4 }

hmWanMbus98Status		OBJECT-TYPE
			SYNTAX	Gauge32
			MAX-ACCESS	read-only
			STATUS	current
			::= { hmWanMbus98 5 }

hmWanMbus98VIF00		OBJECT-TYPE
			SYNTAX	INTEGER
			MAX-ACCESS	read-only
			STATUS	current
			::= { hmWanMbus98 6 }

hmWanMbus98Value00		OBJECT-TYPE
			SYNTAX	INTEGER
			MAX-ACCESS	read-only
			STATUS	current
			::= { hmWanMbus98 7 }

hmWanMbus98VIF01		OBJECT-TYPE
			SYNTAX	INTEGER
			MAX-ACCESS	read-only
			STATUS	current
			::= { hmWanMbus98 8 }

hmWanMbus98Value01		OBJECT-TYPE
			SYNTAX	INTEGER
			MAX-ACCESS	read-only
			STATUS	current
			::= { hmWanMbus98 9 }

hmWanMbus98VIF02		OBJECT-TYPE
			SYNTAX	INTEGER
			MAX-ACCESS	read-only
			STATUS	current
			::= { hmWanMbus98 10 }

hmWanMbus98Value02		OBJECT-TYPE
			SYNTAX	INTEGER
			MAX-ACCESS	read-only
			STATUS	current
			::= { hmWanMbus98 11 }

hmWanMbus98VIF03		OBJECT-TYPE
			SYNTAX	INTEGER
			MAX-ACCESS	read-only
			STATUS	current
			::= { hmWanMbus98 12 }

hmWanMbus98Value03		OBJECT-TYPE
			SYNTAX	INTEGER
			MAX-ACCESS	read-only
			STATUS	current
			::= { hmWanMbus98 13 }

hmWanMbus98VIF04		OBJECT-TYPE
			SYNTAX	INTEGER
			MAX-ACCESS	read-only
			STATUS	current
			::= { hmWanMbus98 14 }

hmWanMbus98Value04		OBJECT-TYPE
			SYNTAX	INTEGER
			MAX-ACCESS	read-only
			STATUS	current
			::= { hmWanMbus98 15 }

hmWanMbus98VIF05		OBJECT-TYPE
			SYNTAX	INTEGER
			MAX-ACCESS	read-only
			STATUS	current
			::= { hmWanMbus98 16 }

hmWanMbus98Value05		OBJECT-TYPE
			SYNTAX	INTEGER
			MAX-ACCESS	read-only
			STATUS	current
			::= { hmWanMbus98 17 }

hmWanMbus98VIF06		OBJECT-TYPE
			SYNTAX	INTEGER
			MAX-ACCESS	read-only
			STATUS	current
			::= { hmWanMbus98 18 }

hmWanMbus98Value06		OBJECT-TYPE
			SYNTAX	INTEGER
			MAX-ACCESS	read-only
			STATUS	current
			::= { hmWanMbus98 19 }

hmWanMbus98VIF07		OBJECT-TYPE
			SYNTAX	INTEGER
			MAX-ACCESS	read-only
			STATUS	current
			::= { hmWanMbus98 20 }

hmWanMbus98Value07		OBJECT-TYPE
			SYNTAX	INTEGER
			MAX-ACCESS	read-only
			STATUS	current
			::= { hmWanMbus98 21 }

hmWanMbus98VIF08		OBJECT-TYPE
			SYNTAX	INTEGER
			MAX-ACCESS	read-only
			STATUS	current
			::= { hmWanMbus98 22 }

hmWanMbus98Value08		OBJECT-TYPE
			SYNTAX	INTEGER
			MAX-ACCESS	read-only
			STATUS	current
			::= { hmWanMbus98 23 }

hmWanMbus98VIF09		OBJECT-TYPE
			SYNTAX	INTEGER
			MAX-ACCESS	read-only
			STATUS	current
			::= { hmWanMbus98 24 }

hmWanMbus98Value09		OBJECT-TYPE
			SYNTAX	INTEGER
			MAX-ACCESS	read-only
			STATUS	current
			::= { hmWanMbus98 25 }

hmWanMbus98VIF0A		OBJECT-TYPE
			SYNTAX	INTEGER
			MAX-ACCESS	read-only
			STATUS	current
			::= { hmWanMbus98 26 }

hmWanMbus98Value0A		OBJECT-TYPE
			SYNTAX	INTEGER
			MAX-ACCESS	read-only
			STATUS	current
			::= { hmWanMbus98 27 }

hmWanMbus98VIF0B		OBJECT-TYPE
			SYNTAX	INTEGER
			MAX-ACCESS	read-only
			STATUS	current
			::= { hmWanMbus98 28 }

hmWanMbus98Value0B		OBJECT-TYPE
			SYNTAX	INTEGER
			MAX-ACCESS	read-only
			STATUS	current
			::= { hmWanMbus98 29 }

hmWanMbus98VIF0C		OBJECT-TYPE
			SYNTAX	INTEGER
			MAX-ACCESS	read-only
			STATUS	current
			::= { hmWanMbus98 30 }

hmWanMbus98Value0C		OBJECT-TYPE
			SYNTAX	INTEGER
			MAX-ACCESS	read-only
			STATUS	current
			::= { hmWanMbus98 31 }

hmWanMbus98VIF0D		OBJECT-TYPE
			SYNTAX	INTEGER
			MAX-ACCESS	read-only
			STATUS	current
			::= { hmWanMbus98 32 }

hmWanMbus98Value0D		OBJECT-TYPE
			SYNTAX	INTEGER
			MAX-ACCESS	read-only
			STATUS	current
			::= { hmWanMbus98 33 }

hmWanMbus98VIF0E		OBJECT-TYPE
			SYNTAX	INTEGER
			MAX-ACCESS	read-only
			STATUS	current
			::= { hmWanMbus98 34 }

hmWanMbus98Value0E		OBJECT-TYPE
			SYNTAX	INTEGER
			MAX-ACCESS	read-only
			STATUS	current
			::= { hmWanMbus98 35 }

hmWanMbus98VIF0F		OBJECT-TYPE
			SYNTAX	INTEGER
			MAX-ACCESS	read-only
			STATUS	current
			::= { hmWanMbus98 36 }

hmWanMbus98Value0F		OBJECT-TYPE
			SYNTAX	INTEGER
			MAX-ACCESS	read-only
			STATUS	current
			::= { hmWanMbus98 37 }

hmWanMbus98VIF10		OBJECT-TYPE
			SYNTAX	INTEGER
			MAX-ACCESS	read-only
			STATUS	current
			::= { hmWanMbus98 38 }

hmWanMbus98Value10		OBJECT-TYPE
			SYNTAX	INTEGER
			MAX-ACCESS	read-only
			STATUS	current
			::= { hmWanMbus98 39 }

hmWanMbus98VIF11		OBJECT-TYPE
			SYNTAX	INTEGER
			MAX-ACCESS	read-only
			STATUS	current
			::= { hmWanMbus98 40 }

hmWanMbus98Value11		OBJECT-TYPE
			SYNTAX	INTEGER
			MAX-ACCESS	read-only
			STATUS	current
			::= { hmWanMbus98 41 }

hmWanMbus98VIF12		OBJECT-TYPE
			SYNTAX	INTEGER
			MAX-ACCESS	read-only
			STATUS	current
			::= { hmWanMbus98 42 }

hmWanMbus98Value12		OBJECT-TYPE
			SYNTAX	INTEGER
			MAX-ACCESS	read-only
			STATUS	current
			::= { hmWanMbus98 43 }

hmWanMbus98VIF13		OBJECT-TYPE
			SYNTAX	INTEGER
			MAX-ACCESS	read-only
			STATUS	current
			::= { hmWanMbus98 44 }

hmWanMbus98Value13		OBJECT-TYPE
			SYNTAX	INTEGER
			MAX-ACCESS	read-only
			STATUS	current
			::= { hmWanMbus98 45 }

hmWanMbus98VIF14		OBJECT-TYPE
			SYNTAX	INTEGER
			MAX-ACCESS	read-only
			STATUS	current
			::= { hmWanMbus98 46 }

hmWanMbus98Value14		OBJECT-TYPE
			SYNTAX	INTEGER
			MAX-ACCESS	read-only
			STATUS	current
			::= { hmWanMbus98 47 }

hmWanMbus98VIF15		OBJECT-TYPE
			SYNTAX	INTEGER
			MAX-ACCESS	read-only
			STATUS	current
			::= { hmWanMbus98 48 }

hmWanMbus98Value15		OBJECT-TYPE
			SYNTAX	INTEGER
			MAX-ACCESS	read-only
			STATUS	current
			::= { hmWanMbus98 49 }

hmWanMbus98VIF16		OBJECT-TYPE
			SYNTAX	INTEGER
			MAX-ACCESS	read-only
			STATUS	current
			::= { hmWanMbus98 50 }

hmWanMbus98Value16		OBJECT-TYPE
			SYNTAX	INTEGER
			MAX-ACCESS	read-only
			STATUS	current
			::= { hmWanMbus98 51 }

hmWanMbus98VIF17		OBJECT-TYPE
			SYNTAX	INTEGER
			MAX-ACCESS	read-only
			STATUS	current
			::= { hmWanMbus98 52 }

hmWanMbus98Value17		OBJECT-TYPE
			SYNTAX	INTEGER
			MAX-ACCESS	read-only
			STATUS	current
			::= { hmWanMbus98 53 }

hmWanMbus98VIF18		OBJECT-TYPE
			SYNTAX	INTEGER
			MAX-ACCESS	read-only
			STATUS	current
			::= { hmWanMbus98 54 }

hmWanMbus98Value18		OBJECT-TYPE
			SYNTAX	INTEGER
			MAX-ACCESS	read-only
			STATUS	current
			::= { hmWanMbus98 55 }

hmWanMbus98VIF19		OBJECT-TYPE
			SYNTAX	INTEGER
			MAX-ACCESS	read-only
			STATUS	current
			::= { hmWanMbus98 56 }

hmWanMbus98Value19		OBJECT-TYPE
			SYNTAX	INTEGER
			MAX-ACCESS	read-only
			STATUS	current
			::= { hmWanMbus98 57 }

hmWanMbus98VIF1A		OBJECT-TYPE
			SYNTAX	INTEGER
			MAX-ACCESS	read-only
			STATUS	current
			::= { hmWanMbus98 58 }

hmWanMbus98Value1A		OBJECT-TYPE
			SYNTAX	INTEGER
			MAX-ACCESS	read-only
			STATUS	current
			::= { hmWanMbus98 59 }

hmWanMbus98VIF1B		OBJECT-TYPE
			SYNTAX	INTEGER
			MAX-ACCESS	read-only
			STATUS	current
			::= { hmWanMbus98 60 }

hmWanMbus98Value1B		OBJECT-TYPE
			SYNTAX	INTEGER
			MAX-ACCESS	read-only
			STATUS	current
			::= { hmWanMbus98 61 }

hmWanMbus98VIF1C		OBJECT-TYPE
			SYNTAX	INTEGER
			MAX-ACCESS	read-only
			STATUS	current
			::= { hmWanMbus98 62 }

hmWanMbus98Value1C		OBJECT-TYPE
			SYNTAX	INTEGER
			MAX-ACCESS	read-only
			STATUS	current
			::= { hmWanMbus98 63 }

hmWanMbus98VIF1D		OBJECT-TYPE
			SYNTAX	INTEGER
			MAX-ACCESS	read-only
			STATUS	current
			::= { hmWanMbus98 64 }

hmWanMbus98Value1D		OBJECT-TYPE
			SYNTAX	INTEGER
			MAX-ACCESS	read-only
			STATUS	current
			::= { hmWanMbus98 65 }

hmWanMbus98VIF1E		OBJECT-TYPE
			SYNTAX	INTEGER
			MAX-ACCESS	read-only
			STATUS	current
			::= { hmWanMbus98 66 }

hmWanMbus98Value1E		OBJECT-TYPE
			SYNTAX	INTEGER
			MAX-ACCESS	read-only
			STATUS	current
			::= { hmWanMbus98 67 }

hmWanMbus98VIF1F		OBJECT-TYPE
			SYNTAX	INTEGER
			MAX-ACCESS	read-only
			STATUS	current
			::= { hmWanMbus98 68 }

hmWanMbus98Value1F		OBJECT-TYPE
			SYNTAX	INTEGER
			MAX-ACCESS	read-only
			STATUS	current
			::= { hmWanMbus98 69 }

hmWanMbus98VIF20		OBJECT-TYPE
			SYNTAX	INTEGER
			MAX-ACCESS	read-only
			STATUS	current
			::= { hmWanMbus98 70 }

hmWanMbus98Value20		OBJECT-TYPE
			SYNTAX	INTEGER
			MAX-ACCESS	read-only
			STATUS	current
			::= { hmWanMbus98 71 }

hmWanMbus98VIF21		OBJECT-TYPE
			SYNTAX	INTEGER
			MAX-ACCESS	read-only
			STATUS	current
			::= { hmWanMbus98 72 }

hmWanMbus98Value21		OBJECT-TYPE
			SYNTAX	INTEGER
			MAX-ACCESS	read-only
			STATUS	current
			::= { hmWanMbus98 73 }

hmWanMbus98VIF22		OBJECT-TYPE
			SYNTAX	INTEGER
			MAX-ACCESS	read-only
			STATUS	current
			::= { hmWanMbus98 74 }

hmWanMbus98Value22		OBJECT-TYPE
			SYNTAX	INTEGER
			MAX-ACCESS	read-only
			STATUS	current
			::= { hmWanMbus98 75 }

hmWanMbus98VIF23		OBJECT-TYPE
			SYNTAX	INTEGER
			MAX-ACCESS	read-only
			STATUS	current
			::= { hmWanMbus98 76 }

hmWanMbus98Value23		OBJECT-TYPE
			SYNTAX	INTEGER
			MAX-ACCESS	read-only
			STATUS	current
			::= { hmWanMbus98 77 }

hmWanMbus98VIF24		OBJECT-TYPE
			SYNTAX	INTEGER
			MAX-ACCESS	read-only
			STATUS	current
			::= { hmWanMbus98 78 }

hmWanMbus98Value24		OBJECT-TYPE
			SYNTAX	INTEGER
			MAX-ACCESS	read-only
			STATUS	current
			::= { hmWanMbus98 79 }

hmWanMbus98VIF25		OBJECT-TYPE
			SYNTAX	INTEGER
			MAX-ACCESS	read-only
			STATUS	current
			::= { hmWanMbus98 80 }

hmWanMbus98Value25		OBJECT-TYPE
			SYNTAX	INTEGER
			MAX-ACCESS	read-only
			STATUS	current
			::= { hmWanMbus98 81 }

hmWanMbus98VIF26		OBJECT-TYPE
			SYNTAX	INTEGER
			MAX-ACCESS	read-only
			STATUS	current
			::= { hmWanMbus98 82 }

hmWanMbus98Value26		OBJECT-TYPE
			SYNTAX	INTEGER
			MAX-ACCESS	read-only
			STATUS	current
			::= { hmWanMbus98 83 }

hmWanMbus98VIF27		OBJECT-TYPE
			SYNTAX	INTEGER
			MAX-ACCESS	read-only
			STATUS	current
			::= { hmWanMbus98 84 }

hmWanMbus98Value27		OBJECT-TYPE
			SYNTAX	INTEGER
			MAX-ACCESS	read-only
			STATUS	current
			::= { hmWanMbus98 85 }

hmWanMbus98VIF28		OBJECT-TYPE
			SYNTAX	INTEGER
			MAX-ACCESS	read-only
			STATUS	current
			::= { hmWanMbus98 86 }

hmWanMbus98Value28		OBJECT-TYPE
			SYNTAX	INTEGER
			MAX-ACCESS	read-only
			STATUS	current
			::= { hmWanMbus98 87 }

hmWanMbus98VIF29		OBJECT-TYPE
			SYNTAX	INTEGER
			MAX-ACCESS	read-only
			STATUS	current
			::= { hmWanMbus98 88 }

hmWanMbus98Value29		OBJECT-TYPE
			SYNTAX	INTEGER
			MAX-ACCESS	read-only
			STATUS	current
			::= { hmWanMbus98 89 }

hmWanMbus98VIF2A		OBJECT-TYPE
			SYNTAX	INTEGER
			MAX-ACCESS	read-only
			STATUS	current
			::= { hmWanMbus98 90 }

hmWanMbus98Value2A		OBJECT-TYPE
			SYNTAX	INTEGER
			MAX-ACCESS	read-only
			STATUS	current
			::= { hmWanMbus98 91 }

hmWanMbus98VIF2B		OBJECT-TYPE
			SYNTAX	INTEGER
			MAX-ACCESS	read-only
			STATUS	current
			::= { hmWanMbus98 92 }

hmWanMbus98Value2B		OBJECT-TYPE
			SYNTAX	INTEGER
			MAX-ACCESS	read-only
			STATUS	current
			::= { hmWanMbus98 93 }

hmWanMbus98VIF2C		OBJECT-TYPE
			SYNTAX	INTEGER
			MAX-ACCESS	read-only
			STATUS	current
			::= { hmWanMbus98 94 }

hmWanMbus98Value2C		OBJECT-TYPE
			SYNTAX	INTEGER
			MAX-ACCESS	read-only
			STATUS	current
			::= { hmWanMbus98 95 }

hmWanMbus98VIF2D		OBJECT-TYPE
			SYNTAX	INTEGER
			MAX-ACCESS	read-only
			STATUS	current
			::= { hmWanMbus98 96 }

hmWanMbus98Value2D		OBJECT-TYPE
			SYNTAX	INTEGER
			MAX-ACCESS	read-only
			STATUS	current
			::= { hmWanMbus98 97 }

hmWanMbus98VIF2E		OBJECT-TYPE
			SYNTAX	INTEGER
			MAX-ACCESS	read-only
			STATUS	current
			::= { hmWanMbus98 98 }

hmWanMbus98Value2E		OBJECT-TYPE
			SYNTAX	INTEGER
			MAX-ACCESS	read-only
			STATUS	current
			::= { hmWanMbus98 99 }

hmWanMbus98VIF2F		OBJECT-TYPE
			SYNTAX	INTEGER
			MAX-ACCESS	read-only
			STATUS	current
			::= { hmWanMbus98 100 }

hmWanMbus98Value2F		OBJECT-TYPE
			SYNTAX	INTEGER
			MAX-ACCESS	read-only
			STATUS	current
			::= { hmWanMbus98 101 }

hmWanMbus99			OBJECT IDENTIFIER ::= { hmWanMbus 153 }

hmWanMbus99IdNumber		OBJECT-TYPE
			SYNTAX	Gauge32
			MAX-ACCESS	read-only
			STATUS	current
			::= { hmWanMbus99 1 }

hmWanMbus99Manufacturer	OBJECT-TYPE
			SYNTAX	Gauge32
			MAX-ACCESS	read-only
			STATUS	current
			::= { hmWanMbus99 2 }

hmWanMbus99Version		OBJECT-TYPE
			SYNTAX	Gauge32
			MAX-ACCESS	read-only
			STATUS	current
			::= { hmWanMbus99 3 }

hmWanMbus99Medium		OBJECT-TYPE
			SYNTAX	Gauge32
			MAX-ACCESS	read-only
			STATUS	current
			::= { hmWanMbus99 4 }

hmWanMbus99Status		OBJECT-TYPE
			SYNTAX	Gauge32
			MAX-ACCESS	read-only
			STATUS	current
			::= { hmWanMbus99 5 }

hmWanMbus99VIF00		OBJECT-TYPE
			SYNTAX	INTEGER
			MAX-ACCESS	read-only
			STATUS	current
			::= { hmWanMbus99 6 }

hmWanMbus99Value00		OBJECT-TYPE
			SYNTAX	INTEGER
			MAX-ACCESS	read-only
			STATUS	current
			::= { hmWanMbus99 7 }

hmWanMbus99VIF01		OBJECT-TYPE
			SYNTAX	INTEGER
			MAX-ACCESS	read-only
			STATUS	current
			::= { hmWanMbus99 8 }

hmWanMbus99Value01		OBJECT-TYPE
			SYNTAX	INTEGER
			MAX-ACCESS	read-only
			STATUS	current
			::= { hmWanMbus99 9 }

hmWanMbus99VIF02		OBJECT-TYPE
			SYNTAX	INTEGER
			MAX-ACCESS	read-only
			STATUS	current
			::= { hmWanMbus99 10 }

hmWanMbus99Value02		OBJECT-TYPE
			SYNTAX	INTEGER
			MAX-ACCESS	read-only
			STATUS	current
			::= { hmWanMbus99 11 }

hmWanMbus99VIF03		OBJECT-TYPE
			SYNTAX	INTEGER
			MAX-ACCESS	read-only
			STATUS	current
			::= { hmWanMbus99 12 }

hmWanMbus99Value03		OBJECT-TYPE
			SYNTAX	INTEGER
			MAX-ACCESS	read-only
			STATUS	current
			::= { hmWanMbus99 13 }

hmWanMbus99VIF04		OBJECT-TYPE
			SYNTAX	INTEGER
			MAX-ACCESS	read-only
			STATUS	current
			::= { hmWanMbus99 14 }

hmWanMbus99Value04		OBJECT-TYPE
			SYNTAX	INTEGER
			MAX-ACCESS	read-only
			STATUS	current
			::= { hmWanMbus99 15 }

hmWanMbus99VIF05		OBJECT-TYPE
			SYNTAX	INTEGER
			MAX-ACCESS	read-only
			STATUS	current
			::= { hmWanMbus99 16 }

hmWanMbus99Value05		OBJECT-TYPE
			SYNTAX	INTEGER
			MAX-ACCESS	read-only
			STATUS	current
			::= { hmWanMbus99 17 }

hmWanMbus99VIF06		OBJECT-TYPE
			SYNTAX	INTEGER
			MAX-ACCESS	read-only
			STATUS	current
			::= { hmWanMbus99 18 }

hmWanMbus99Value06		OBJECT-TYPE
			SYNTAX	INTEGER
			MAX-ACCESS	read-only
			STATUS	current
			::= { hmWanMbus99 19 }

hmWanMbus99VIF07		OBJECT-TYPE
			SYNTAX	INTEGER
			MAX-ACCESS	read-only
			STATUS	current
			::= { hmWanMbus99 20 }

hmWanMbus99Value07		OBJECT-TYPE
			SYNTAX	INTEGER
			MAX-ACCESS	read-only
			STATUS	current
			::= { hmWanMbus99 21 }

hmWanMbus99VIF08		OBJECT-TYPE
			SYNTAX	INTEGER
			MAX-ACCESS	read-only
			STATUS	current
			::= { hmWanMbus99 22 }

hmWanMbus99Value08		OBJECT-TYPE
			SYNTAX	INTEGER
			MAX-ACCESS	read-only
			STATUS	current
			::= { hmWanMbus99 23 }

hmWanMbus99VIF09		OBJECT-TYPE
			SYNTAX	INTEGER
			MAX-ACCESS	read-only
			STATUS	current
			::= { hmWanMbus99 24 }

hmWanMbus99Value09		OBJECT-TYPE
			SYNTAX	INTEGER
			MAX-ACCESS	read-only
			STATUS	current
			::= { hmWanMbus99 25 }

hmWanMbus99VIF0A		OBJECT-TYPE
			SYNTAX	INTEGER
			MAX-ACCESS	read-only
			STATUS	current
			::= { hmWanMbus99 26 }

hmWanMbus99Value0A		OBJECT-TYPE
			SYNTAX	INTEGER
			MAX-ACCESS	read-only
			STATUS	current
			::= { hmWanMbus99 27 }

hmWanMbus99VIF0B		OBJECT-TYPE
			SYNTAX	INTEGER
			MAX-ACCESS	read-only
			STATUS	current
			::= { hmWanMbus99 28 }

hmWanMbus99Value0B		OBJECT-TYPE
			SYNTAX	INTEGER
			MAX-ACCESS	read-only
			STATUS	current
			::= { hmWanMbus99 29 }

hmWanMbus99VIF0C		OBJECT-TYPE
			SYNTAX	INTEGER
			MAX-ACCESS	read-only
			STATUS	current
			::= { hmWanMbus99 30 }

hmWanMbus99Value0C		OBJECT-TYPE
			SYNTAX	INTEGER
			MAX-ACCESS	read-only
			STATUS	current
			::= { hmWanMbus99 31 }

hmWanMbus99VIF0D		OBJECT-TYPE
			SYNTAX	INTEGER
			MAX-ACCESS	read-only
			STATUS	current
			::= { hmWanMbus99 32 }

hmWanMbus99Value0D		OBJECT-TYPE
			SYNTAX	INTEGER
			MAX-ACCESS	read-only
			STATUS	current
			::= { hmWanMbus99 33 }

hmWanMbus99VIF0E		OBJECT-TYPE
			SYNTAX	INTEGER
			MAX-ACCESS	read-only
			STATUS	current
			::= { hmWanMbus99 34 }

hmWanMbus99Value0E		OBJECT-TYPE
			SYNTAX	INTEGER
			MAX-ACCESS	read-only
			STATUS	current
			::= { hmWanMbus99 35 }

hmWanMbus99VIF0F		OBJECT-TYPE
			SYNTAX	INTEGER
			MAX-ACCESS	read-only
			STATUS	current
			::= { hmWanMbus99 36 }

hmWanMbus99Value0F		OBJECT-TYPE
			SYNTAX	INTEGER
			MAX-ACCESS	read-only
			STATUS	current
			::= { hmWanMbus99 37 }

hmWanMbus99VIF10		OBJECT-TYPE
			SYNTAX	INTEGER
			MAX-ACCESS	read-only
			STATUS	current
			::= { hmWanMbus99 38 }

hmWanMbus99Value10		OBJECT-TYPE
			SYNTAX	INTEGER
			MAX-ACCESS	read-only
			STATUS	current
			::= { hmWanMbus99 39 }

hmWanMbus99VIF11		OBJECT-TYPE
			SYNTAX	INTEGER
			MAX-ACCESS	read-only
			STATUS	current
			::= { hmWanMbus99 40 }

hmWanMbus99Value11		OBJECT-TYPE
			SYNTAX	INTEGER
			MAX-ACCESS	read-only
			STATUS	current
			::= { hmWanMbus99 41 }

hmWanMbus99VIF12		OBJECT-TYPE
			SYNTAX	INTEGER
			MAX-ACCESS	read-only
			STATUS	current
			::= { hmWanMbus99 42 }

hmWanMbus99Value12		OBJECT-TYPE
			SYNTAX	INTEGER
			MAX-ACCESS	read-only
			STATUS	current
			::= { hmWanMbus99 43 }

hmWanMbus99VIF13		OBJECT-TYPE
			SYNTAX	INTEGER
			MAX-ACCESS	read-only
			STATUS	current
			::= { hmWanMbus99 44 }

hmWanMbus99Value13		OBJECT-TYPE
			SYNTAX	INTEGER
			MAX-ACCESS	read-only
			STATUS	current
			::= { hmWanMbus99 45 }

hmWanMbus99VIF14		OBJECT-TYPE
			SYNTAX	INTEGER
			MAX-ACCESS	read-only
			STATUS	current
			::= { hmWanMbus99 46 }

hmWanMbus99Value14		OBJECT-TYPE
			SYNTAX	INTEGER
			MAX-ACCESS	read-only
			STATUS	current
			::= { hmWanMbus99 47 }

hmWanMbus99VIF15		OBJECT-TYPE
			SYNTAX	INTEGER
			MAX-ACCESS	read-only
			STATUS	current
			::= { hmWanMbus99 48 }

hmWanMbus99Value15		OBJECT-TYPE
			SYNTAX	INTEGER
			MAX-ACCESS	read-only
			STATUS	current
			::= { hmWanMbus99 49 }

hmWanMbus99VIF16		OBJECT-TYPE
			SYNTAX	INTEGER
			MAX-ACCESS	read-only
			STATUS	current
			::= { hmWanMbus99 50 }

hmWanMbus99Value16		OBJECT-TYPE
			SYNTAX	INTEGER
			MAX-ACCESS	read-only
			STATUS	current
			::= { hmWanMbus99 51 }

hmWanMbus99VIF17		OBJECT-TYPE
			SYNTAX	INTEGER
			MAX-ACCESS	read-only
			STATUS	current
			::= { hmWanMbus99 52 }

hmWanMbus99Value17		OBJECT-TYPE
			SYNTAX	INTEGER
			MAX-ACCESS	read-only
			STATUS	current
			::= { hmWanMbus99 53 }

hmWanMbus99VIF18		OBJECT-TYPE
			SYNTAX	INTEGER
			MAX-ACCESS	read-only
			STATUS	current
			::= { hmWanMbus99 54 }

hmWanMbus99Value18		OBJECT-TYPE
			SYNTAX	INTEGER
			MAX-ACCESS	read-only
			STATUS	current
			::= { hmWanMbus99 55 }

hmWanMbus99VIF19		OBJECT-TYPE
			SYNTAX	INTEGER
			MAX-ACCESS	read-only
			STATUS	current
			::= { hmWanMbus99 56 }

hmWanMbus99Value19		OBJECT-TYPE
			SYNTAX	INTEGER
			MAX-ACCESS	read-only
			STATUS	current
			::= { hmWanMbus99 57 }

hmWanMbus99VIF1A		OBJECT-TYPE
			SYNTAX	INTEGER
			MAX-ACCESS	read-only
			STATUS	current
			::= { hmWanMbus99 58 }

hmWanMbus99Value1A		OBJECT-TYPE
			SYNTAX	INTEGER
			MAX-ACCESS	read-only
			STATUS	current
			::= { hmWanMbus99 59 }

hmWanMbus99VIF1B		OBJECT-TYPE
			SYNTAX	INTEGER
			MAX-ACCESS	read-only
			STATUS	current
			::= { hmWanMbus99 60 }

hmWanMbus99Value1B		OBJECT-TYPE
			SYNTAX	INTEGER
			MAX-ACCESS	read-only
			STATUS	current
			::= { hmWanMbus99 61 }

hmWanMbus99VIF1C		OBJECT-TYPE
			SYNTAX	INTEGER
			MAX-ACCESS	read-only
			STATUS	current
			::= { hmWanMbus99 62 }

hmWanMbus99Value1C		OBJECT-TYPE
			SYNTAX	INTEGER
			MAX-ACCESS	read-only
			STATUS	current
			::= { hmWanMbus99 63 }

hmWanMbus99VIF1D		OBJECT-TYPE
			SYNTAX	INTEGER
			MAX-ACCESS	read-only
			STATUS	current
			::= { hmWanMbus99 64 }

hmWanMbus99Value1D		OBJECT-TYPE
			SYNTAX	INTEGER
			MAX-ACCESS	read-only
			STATUS	current
			::= { hmWanMbus99 65 }

hmWanMbus99VIF1E		OBJECT-TYPE
			SYNTAX	INTEGER
			MAX-ACCESS	read-only
			STATUS	current
			::= { hmWanMbus99 66 }

hmWanMbus99Value1E		OBJECT-TYPE
			SYNTAX	INTEGER
			MAX-ACCESS	read-only
			STATUS	current
			::= { hmWanMbus99 67 }

hmWanMbus99VIF1F		OBJECT-TYPE
			SYNTAX	INTEGER
			MAX-ACCESS	read-only
			STATUS	current
			::= { hmWanMbus99 68 }

hmWanMbus99Value1F		OBJECT-TYPE
			SYNTAX	INTEGER
			MAX-ACCESS	read-only
			STATUS	current
			::= { hmWanMbus99 69 }

hmWanMbus99VIF20		OBJECT-TYPE
			SYNTAX	INTEGER
			MAX-ACCESS	read-only
			STATUS	current
			::= { hmWanMbus99 70 }

hmWanMbus99Value20		OBJECT-TYPE
			SYNTAX	INTEGER
			MAX-ACCESS	read-only
			STATUS	current
			::= { hmWanMbus99 71 }

hmWanMbus99VIF21		OBJECT-TYPE
			SYNTAX	INTEGER
			MAX-ACCESS	read-only
			STATUS	current
			::= { hmWanMbus99 72 }

hmWanMbus99Value21		OBJECT-TYPE
			SYNTAX	INTEGER
			MAX-ACCESS	read-only
			STATUS	current
			::= { hmWanMbus99 73 }

hmWanMbus99VIF22		OBJECT-TYPE
			SYNTAX	INTEGER
			MAX-ACCESS	read-only
			STATUS	current
			::= { hmWanMbus99 74 }

hmWanMbus99Value22		OBJECT-TYPE
			SYNTAX	INTEGER
			MAX-ACCESS	read-only
			STATUS	current
			::= { hmWanMbus99 75 }

hmWanMbus99VIF23		OBJECT-TYPE
			SYNTAX	INTEGER
			MAX-ACCESS	read-only
			STATUS	current
			::= { hmWanMbus99 76 }

hmWanMbus99Value23		OBJECT-TYPE
			SYNTAX	INTEGER
			MAX-ACCESS	read-only
			STATUS	current
			::= { hmWanMbus99 77 }

hmWanMbus99VIF24		OBJECT-TYPE
			SYNTAX	INTEGER
			MAX-ACCESS	read-only
			STATUS	current
			::= { hmWanMbus99 78 }

hmWanMbus99Value24		OBJECT-TYPE
			SYNTAX	INTEGER
			MAX-ACCESS	read-only
			STATUS	current
			::= { hmWanMbus99 79 }

hmWanMbus99VIF25		OBJECT-TYPE
			SYNTAX	INTEGER
			MAX-ACCESS	read-only
			STATUS	current
			::= { hmWanMbus99 80 }

hmWanMbus99Value25		OBJECT-TYPE
			SYNTAX	INTEGER
			MAX-ACCESS	read-only
			STATUS	current
			::= { hmWanMbus99 81 }

hmWanMbus99VIF26		OBJECT-TYPE
			SYNTAX	INTEGER
			MAX-ACCESS	read-only
			STATUS	current
			::= { hmWanMbus99 82 }

hmWanMbus99Value26		OBJECT-TYPE
			SYNTAX	INTEGER
			MAX-ACCESS	read-only
			STATUS	current
			::= { hmWanMbus99 83 }

hmWanMbus99VIF27		OBJECT-TYPE
			SYNTAX	INTEGER
			MAX-ACCESS	read-only
			STATUS	current
			::= { hmWanMbus99 84 }

hmWanMbus99Value27		OBJECT-TYPE
			SYNTAX	INTEGER
			MAX-ACCESS	read-only
			STATUS	current
			::= { hmWanMbus99 85 }

hmWanMbus99VIF28		OBJECT-TYPE
			SYNTAX	INTEGER
			MAX-ACCESS	read-only
			STATUS	current
			::= { hmWanMbus99 86 }

hmWanMbus99Value28		OBJECT-TYPE
			SYNTAX	INTEGER
			MAX-ACCESS	read-only
			STATUS	current
			::= { hmWanMbus99 87 }

hmWanMbus99VIF29		OBJECT-TYPE
			SYNTAX	INTEGER
			MAX-ACCESS	read-only
			STATUS	current
			::= { hmWanMbus99 88 }

hmWanMbus99Value29		OBJECT-TYPE
			SYNTAX	INTEGER
			MAX-ACCESS	read-only
			STATUS	current
			::= { hmWanMbus99 89 }

hmWanMbus99VIF2A		OBJECT-TYPE
			SYNTAX	INTEGER
			MAX-ACCESS	read-only
			STATUS	current
			::= { hmWanMbus99 90 }

hmWanMbus99Value2A		OBJECT-TYPE
			SYNTAX	INTEGER
			MAX-ACCESS	read-only
			STATUS	current
			::= { hmWanMbus99 91 }

hmWanMbus99VIF2B		OBJECT-TYPE
			SYNTAX	INTEGER
			MAX-ACCESS	read-only
			STATUS	current
			::= { hmWanMbus99 92 }

hmWanMbus99Value2B		OBJECT-TYPE
			SYNTAX	INTEGER
			MAX-ACCESS	read-only
			STATUS	current
			::= { hmWanMbus99 93 }

hmWanMbus99VIF2C		OBJECT-TYPE
			SYNTAX	INTEGER
			MAX-ACCESS	read-only
			STATUS	current
			::= { hmWanMbus99 94 }

hmWanMbus99Value2C		OBJECT-TYPE
			SYNTAX	INTEGER
			MAX-ACCESS	read-only
			STATUS	current
			::= { hmWanMbus99 95 }

hmWanMbus99VIF2D		OBJECT-TYPE
			SYNTAX	INTEGER
			MAX-ACCESS	read-only
			STATUS	current
			::= { hmWanMbus99 96 }

hmWanMbus99Value2D		OBJECT-TYPE
			SYNTAX	INTEGER
			MAX-ACCESS	read-only
			STATUS	current
			::= { hmWanMbus99 97 }

hmWanMbus99VIF2E		OBJECT-TYPE
			SYNTAX	INTEGER
			MAX-ACCESS	read-only
			STATUS	current
			::= { hmWanMbus99 98 }

hmWanMbus99Value2E		OBJECT-TYPE
			SYNTAX	INTEGER
			MAX-ACCESS	read-only
			STATUS	current
			::= { hmWanMbus99 99 }

hmWanMbus99VIF2F		OBJECT-TYPE
			SYNTAX	INTEGER
			MAX-ACCESS	read-only
			STATUS	current
			::= { hmWanMbus99 100 }

hmWanMbus99Value2F		OBJECT-TYPE
			SYNTAX	INTEGER
			MAX-ACCESS	read-only
			STATUS	current
			::= { hmWanMbus99 101 }

hmWanMbus9A			OBJECT IDENTIFIER ::= { hmWanMbus 154 }

hmWanMbus9AIdNumber		OBJECT-TYPE
			SYNTAX	Gauge32
			MAX-ACCESS	read-only
			STATUS	current
			::= { hmWanMbus9A 1 }

hmWanMbus9AManufacturer	OBJECT-TYPE
			SYNTAX	Gauge32
			MAX-ACCESS	read-only
			STATUS	current
			::= { hmWanMbus9A 2 }

hmWanMbus9AVersion		OBJECT-TYPE
			SYNTAX	Gauge32
			MAX-ACCESS	read-only
			STATUS	current
			::= { hmWanMbus9A 3 }

hmWanMbus9AMedium		OBJECT-TYPE
			SYNTAX	Gauge32
			MAX-ACCESS	read-only
			STATUS	current
			::= { hmWanMbus9A 4 }

hmWanMbus9AStatus		OBJECT-TYPE
			SYNTAX	Gauge32
			MAX-ACCESS	read-only
			STATUS	current
			::= { hmWanMbus9A 5 }

hmWanMbus9AVIF00		OBJECT-TYPE
			SYNTAX	INTEGER
			MAX-ACCESS	read-only
			STATUS	current
			::= { hmWanMbus9A 6 }

hmWanMbus9AValue00		OBJECT-TYPE
			SYNTAX	INTEGER
			MAX-ACCESS	read-only
			STATUS	current
			::= { hmWanMbus9A 7 }

hmWanMbus9AVIF01		OBJECT-TYPE
			SYNTAX	INTEGER
			MAX-ACCESS	read-only
			STATUS	current
			::= { hmWanMbus9A 8 }

hmWanMbus9AValue01		OBJECT-TYPE
			SYNTAX	INTEGER
			MAX-ACCESS	read-only
			STATUS	current
			::= { hmWanMbus9A 9 }

hmWanMbus9AVIF02		OBJECT-TYPE
			SYNTAX	INTEGER
			MAX-ACCESS	read-only
			STATUS	current
			::= { hmWanMbus9A 10 }

hmWanMbus9AValue02		OBJECT-TYPE
			SYNTAX	INTEGER
			MAX-ACCESS	read-only
			STATUS	current
			::= { hmWanMbus9A 11 }

hmWanMbus9AVIF03		OBJECT-TYPE
			SYNTAX	INTEGER
			MAX-ACCESS	read-only
			STATUS	current
			::= { hmWanMbus9A 12 }

hmWanMbus9AValue03		OBJECT-TYPE
			SYNTAX	INTEGER
			MAX-ACCESS	read-only
			STATUS	current
			::= { hmWanMbus9A 13 }

hmWanMbus9AVIF04		OBJECT-TYPE
			SYNTAX	INTEGER
			MAX-ACCESS	read-only
			STATUS	current
			::= { hmWanMbus9A 14 }

hmWanMbus9AValue04		OBJECT-TYPE
			SYNTAX	INTEGER
			MAX-ACCESS	read-only
			STATUS	current
			::= { hmWanMbus9A 15 }

hmWanMbus9AVIF05		OBJECT-TYPE
			SYNTAX	INTEGER
			MAX-ACCESS	read-only
			STATUS	current
			::= { hmWanMbus9A 16 }

hmWanMbus9AValue05		OBJECT-TYPE
			SYNTAX	INTEGER
			MAX-ACCESS	read-only
			STATUS	current
			::= { hmWanMbus9A 17 }

hmWanMbus9AVIF06		OBJECT-TYPE
			SYNTAX	INTEGER
			MAX-ACCESS	read-only
			STATUS	current
			::= { hmWanMbus9A 18 }

hmWanMbus9AValue06		OBJECT-TYPE
			SYNTAX	INTEGER
			MAX-ACCESS	read-only
			STATUS	current
			::= { hmWanMbus9A 19 }

hmWanMbus9AVIF07		OBJECT-TYPE
			SYNTAX	INTEGER
			MAX-ACCESS	read-only
			STATUS	current
			::= { hmWanMbus9A 20 }

hmWanMbus9AValue07		OBJECT-TYPE
			SYNTAX	INTEGER
			MAX-ACCESS	read-only
			STATUS	current
			::= { hmWanMbus9A 21 }

hmWanMbus9AVIF08		OBJECT-TYPE
			SYNTAX	INTEGER
			MAX-ACCESS	read-only
			STATUS	current
			::= { hmWanMbus9A 22 }

hmWanMbus9AValue08		OBJECT-TYPE
			SYNTAX	INTEGER
			MAX-ACCESS	read-only
			STATUS	current
			::= { hmWanMbus9A 23 }

hmWanMbus9AVIF09		OBJECT-TYPE
			SYNTAX	INTEGER
			MAX-ACCESS	read-only
			STATUS	current
			::= { hmWanMbus9A 24 }

hmWanMbus9AValue09		OBJECT-TYPE
			SYNTAX	INTEGER
			MAX-ACCESS	read-only
			STATUS	current
			::= { hmWanMbus9A 25 }

hmWanMbus9AVIF0A		OBJECT-TYPE
			SYNTAX	INTEGER
			MAX-ACCESS	read-only
			STATUS	current
			::= { hmWanMbus9A 26 }

hmWanMbus9AValue0A		OBJECT-TYPE
			SYNTAX	INTEGER
			MAX-ACCESS	read-only
			STATUS	current
			::= { hmWanMbus9A 27 }

hmWanMbus9AVIF0B		OBJECT-TYPE
			SYNTAX	INTEGER
			MAX-ACCESS	read-only
			STATUS	current
			::= { hmWanMbus9A 28 }

hmWanMbus9AValue0B		OBJECT-TYPE
			SYNTAX	INTEGER
			MAX-ACCESS	read-only
			STATUS	current
			::= { hmWanMbus9A 29 }

hmWanMbus9AVIF0C		OBJECT-TYPE
			SYNTAX	INTEGER
			MAX-ACCESS	read-only
			STATUS	current
			::= { hmWanMbus9A 30 }

hmWanMbus9AValue0C		OBJECT-TYPE
			SYNTAX	INTEGER
			MAX-ACCESS	read-only
			STATUS	current
			::= { hmWanMbus9A 31 }

hmWanMbus9AVIF0D		OBJECT-TYPE
			SYNTAX	INTEGER
			MAX-ACCESS	read-only
			STATUS	current
			::= { hmWanMbus9A 32 }

hmWanMbus9AValue0D		OBJECT-TYPE
			SYNTAX	INTEGER
			MAX-ACCESS	read-only
			STATUS	current
			::= { hmWanMbus9A 33 }

hmWanMbus9AVIF0E		OBJECT-TYPE
			SYNTAX	INTEGER
			MAX-ACCESS	read-only
			STATUS	current
			::= { hmWanMbus9A 34 }

hmWanMbus9AValue0E		OBJECT-TYPE
			SYNTAX	INTEGER
			MAX-ACCESS	read-only
			STATUS	current
			::= { hmWanMbus9A 35 }

hmWanMbus9AVIF0F		OBJECT-TYPE
			SYNTAX	INTEGER
			MAX-ACCESS	read-only
			STATUS	current
			::= { hmWanMbus9A 36 }

hmWanMbus9AValue0F		OBJECT-TYPE
			SYNTAX	INTEGER
			MAX-ACCESS	read-only
			STATUS	current
			::= { hmWanMbus9A 37 }

hmWanMbus9AVIF10		OBJECT-TYPE
			SYNTAX	INTEGER
			MAX-ACCESS	read-only
			STATUS	current
			::= { hmWanMbus9A 38 }

hmWanMbus9AValue10		OBJECT-TYPE
			SYNTAX	INTEGER
			MAX-ACCESS	read-only
			STATUS	current
			::= { hmWanMbus9A 39 }

hmWanMbus9AVIF11		OBJECT-TYPE
			SYNTAX	INTEGER
			MAX-ACCESS	read-only
			STATUS	current
			::= { hmWanMbus9A 40 }

hmWanMbus9AValue11		OBJECT-TYPE
			SYNTAX	INTEGER
			MAX-ACCESS	read-only
			STATUS	current
			::= { hmWanMbus9A 41 }

hmWanMbus9AVIF12		OBJECT-TYPE
			SYNTAX	INTEGER
			MAX-ACCESS	read-only
			STATUS	current
			::= { hmWanMbus9A 42 }

hmWanMbus9AValue12		OBJECT-TYPE
			SYNTAX	INTEGER
			MAX-ACCESS	read-only
			STATUS	current
			::= { hmWanMbus9A 43 }

hmWanMbus9AVIF13		OBJECT-TYPE
			SYNTAX	INTEGER
			MAX-ACCESS	read-only
			STATUS	current
			::= { hmWanMbus9A 44 }

hmWanMbus9AValue13		OBJECT-TYPE
			SYNTAX	INTEGER
			MAX-ACCESS	read-only
			STATUS	current
			::= { hmWanMbus9A 45 }

hmWanMbus9AVIF14		OBJECT-TYPE
			SYNTAX	INTEGER
			MAX-ACCESS	read-only
			STATUS	current
			::= { hmWanMbus9A 46 }

hmWanMbus9AValue14		OBJECT-TYPE
			SYNTAX	INTEGER
			MAX-ACCESS	read-only
			STATUS	current
			::= { hmWanMbus9A 47 }

hmWanMbus9AVIF15		OBJECT-TYPE
			SYNTAX	INTEGER
			MAX-ACCESS	read-only
			STATUS	current
			::= { hmWanMbus9A 48 }

hmWanMbus9AValue15		OBJECT-TYPE
			SYNTAX	INTEGER
			MAX-ACCESS	read-only
			STATUS	current
			::= { hmWanMbus9A 49 }

hmWanMbus9AVIF16		OBJECT-TYPE
			SYNTAX	INTEGER
			MAX-ACCESS	read-only
			STATUS	current
			::= { hmWanMbus9A 50 }

hmWanMbus9AValue16		OBJECT-TYPE
			SYNTAX	INTEGER
			MAX-ACCESS	read-only
			STATUS	current
			::= { hmWanMbus9A 51 }

hmWanMbus9AVIF17		OBJECT-TYPE
			SYNTAX	INTEGER
			MAX-ACCESS	read-only
			STATUS	current
			::= { hmWanMbus9A 52 }

hmWanMbus9AValue17		OBJECT-TYPE
			SYNTAX	INTEGER
			MAX-ACCESS	read-only
			STATUS	current
			::= { hmWanMbus9A 53 }

hmWanMbus9AVIF18		OBJECT-TYPE
			SYNTAX	INTEGER
			MAX-ACCESS	read-only
			STATUS	current
			::= { hmWanMbus9A 54 }

hmWanMbus9AValue18		OBJECT-TYPE
			SYNTAX	INTEGER
			MAX-ACCESS	read-only
			STATUS	current
			::= { hmWanMbus9A 55 }

hmWanMbus9AVIF19		OBJECT-TYPE
			SYNTAX	INTEGER
			MAX-ACCESS	read-only
			STATUS	current
			::= { hmWanMbus9A 56 }

hmWanMbus9AValue19		OBJECT-TYPE
			SYNTAX	INTEGER
			MAX-ACCESS	read-only
			STATUS	current
			::= { hmWanMbus9A 57 }

hmWanMbus9AVIF1A		OBJECT-TYPE
			SYNTAX	INTEGER
			MAX-ACCESS	read-only
			STATUS	current
			::= { hmWanMbus9A 58 }

hmWanMbus9AValue1A		OBJECT-TYPE
			SYNTAX	INTEGER
			MAX-ACCESS	read-only
			STATUS	current
			::= { hmWanMbus9A 59 }

hmWanMbus9AVIF1B		OBJECT-TYPE
			SYNTAX	INTEGER
			MAX-ACCESS	read-only
			STATUS	current
			::= { hmWanMbus9A 60 }

hmWanMbus9AValue1B		OBJECT-TYPE
			SYNTAX	INTEGER
			MAX-ACCESS	read-only
			STATUS	current
			::= { hmWanMbus9A 61 }

hmWanMbus9AVIF1C		OBJECT-TYPE
			SYNTAX	INTEGER
			MAX-ACCESS	read-only
			STATUS	current
			::= { hmWanMbus9A 62 }

hmWanMbus9AValue1C		OBJECT-TYPE
			SYNTAX	INTEGER
			MAX-ACCESS	read-only
			STATUS	current
			::= { hmWanMbus9A 63 }

hmWanMbus9AVIF1D		OBJECT-TYPE
			SYNTAX	INTEGER
			MAX-ACCESS	read-only
			STATUS	current
			::= { hmWanMbus9A 64 }

hmWanMbus9AValue1D		OBJECT-TYPE
			SYNTAX	INTEGER
			MAX-ACCESS	read-only
			STATUS	current
			::= { hmWanMbus9A 65 }

hmWanMbus9AVIF1E		OBJECT-TYPE
			SYNTAX	INTEGER
			MAX-ACCESS	read-only
			STATUS	current
			::= { hmWanMbus9A 66 }

hmWanMbus9AValue1E		OBJECT-TYPE
			SYNTAX	INTEGER
			MAX-ACCESS	read-only
			STATUS	current
			::= { hmWanMbus9A 67 }

hmWanMbus9AVIF1F		OBJECT-TYPE
			SYNTAX	INTEGER
			MAX-ACCESS	read-only
			STATUS	current
			::= { hmWanMbus9A 68 }

hmWanMbus9AValue1F		OBJECT-TYPE
			SYNTAX	INTEGER
			MAX-ACCESS	read-only
			STATUS	current
			::= { hmWanMbus9A 69 }

hmWanMbus9AVIF20		OBJECT-TYPE
			SYNTAX	INTEGER
			MAX-ACCESS	read-only
			STATUS	current
			::= { hmWanMbus9A 70 }

hmWanMbus9AValue20		OBJECT-TYPE
			SYNTAX	INTEGER
			MAX-ACCESS	read-only
			STATUS	current
			::= { hmWanMbus9A 71 }

hmWanMbus9AVIF21		OBJECT-TYPE
			SYNTAX	INTEGER
			MAX-ACCESS	read-only
			STATUS	current
			::= { hmWanMbus9A 72 }

hmWanMbus9AValue21		OBJECT-TYPE
			SYNTAX	INTEGER
			MAX-ACCESS	read-only
			STATUS	current
			::= { hmWanMbus9A 73 }

hmWanMbus9AVIF22		OBJECT-TYPE
			SYNTAX	INTEGER
			MAX-ACCESS	read-only
			STATUS	current
			::= { hmWanMbus9A 74 }

hmWanMbus9AValue22		OBJECT-TYPE
			SYNTAX	INTEGER
			MAX-ACCESS	read-only
			STATUS	current
			::= { hmWanMbus9A 75 }

hmWanMbus9AVIF23		OBJECT-TYPE
			SYNTAX	INTEGER
			MAX-ACCESS	read-only
			STATUS	current
			::= { hmWanMbus9A 76 }

hmWanMbus9AValue23		OBJECT-TYPE
			SYNTAX	INTEGER
			MAX-ACCESS	read-only
			STATUS	current
			::= { hmWanMbus9A 77 }

hmWanMbus9AVIF24		OBJECT-TYPE
			SYNTAX	INTEGER
			MAX-ACCESS	read-only
			STATUS	current
			::= { hmWanMbus9A 78 }

hmWanMbus9AValue24		OBJECT-TYPE
			SYNTAX	INTEGER
			MAX-ACCESS	read-only
			STATUS	current
			::= { hmWanMbus9A 79 }

hmWanMbus9AVIF25		OBJECT-TYPE
			SYNTAX	INTEGER
			MAX-ACCESS	read-only
			STATUS	current
			::= { hmWanMbus9A 80 }

hmWanMbus9AValue25		OBJECT-TYPE
			SYNTAX	INTEGER
			MAX-ACCESS	read-only
			STATUS	current
			::= { hmWanMbus9A 81 }

hmWanMbus9AVIF26		OBJECT-TYPE
			SYNTAX	INTEGER
			MAX-ACCESS	read-only
			STATUS	current
			::= { hmWanMbus9A 82 }

hmWanMbus9AValue26		OBJECT-TYPE
			SYNTAX	INTEGER
			MAX-ACCESS	read-only
			STATUS	current
			::= { hmWanMbus9A 83 }

hmWanMbus9AVIF27		OBJECT-TYPE
			SYNTAX	INTEGER
			MAX-ACCESS	read-only
			STATUS	current
			::= { hmWanMbus9A 84 }

hmWanMbus9AValue27		OBJECT-TYPE
			SYNTAX	INTEGER
			MAX-ACCESS	read-only
			STATUS	current
			::= { hmWanMbus9A 85 }

hmWanMbus9AVIF28		OBJECT-TYPE
			SYNTAX	INTEGER
			MAX-ACCESS	read-only
			STATUS	current
			::= { hmWanMbus9A 86 }

hmWanMbus9AValue28		OBJECT-TYPE
			SYNTAX	INTEGER
			MAX-ACCESS	read-only
			STATUS	current
			::= { hmWanMbus9A 87 }

hmWanMbus9AVIF29		OBJECT-TYPE
			SYNTAX	INTEGER
			MAX-ACCESS	read-only
			STATUS	current
			::= { hmWanMbus9A 88 }

hmWanMbus9AValue29		OBJECT-TYPE
			SYNTAX	INTEGER
			MAX-ACCESS	read-only
			STATUS	current
			::= { hmWanMbus9A 89 }

hmWanMbus9AVIF2A		OBJECT-TYPE
			SYNTAX	INTEGER
			MAX-ACCESS	read-only
			STATUS	current
			::= { hmWanMbus9A 90 }

hmWanMbus9AValue2A		OBJECT-TYPE
			SYNTAX	INTEGER
			MAX-ACCESS	read-only
			STATUS	current
			::= { hmWanMbus9A 91 }

hmWanMbus9AVIF2B		OBJECT-TYPE
			SYNTAX	INTEGER
			MAX-ACCESS	read-only
			STATUS	current
			::= { hmWanMbus9A 92 }

hmWanMbus9AValue2B		OBJECT-TYPE
			SYNTAX	INTEGER
			MAX-ACCESS	read-only
			STATUS	current
			::= { hmWanMbus9A 93 }

hmWanMbus9AVIF2C		OBJECT-TYPE
			SYNTAX	INTEGER
			MAX-ACCESS	read-only
			STATUS	current
			::= { hmWanMbus9A 94 }

hmWanMbus9AValue2C		OBJECT-TYPE
			SYNTAX	INTEGER
			MAX-ACCESS	read-only
			STATUS	current
			::= { hmWanMbus9A 95 }

hmWanMbus9AVIF2D		OBJECT-TYPE
			SYNTAX	INTEGER
			MAX-ACCESS	read-only
			STATUS	current
			::= { hmWanMbus9A 96 }

hmWanMbus9AValue2D		OBJECT-TYPE
			SYNTAX	INTEGER
			MAX-ACCESS	read-only
			STATUS	current
			::= { hmWanMbus9A 97 }

hmWanMbus9AVIF2E		OBJECT-TYPE
			SYNTAX	INTEGER
			MAX-ACCESS	read-only
			STATUS	current
			::= { hmWanMbus9A 98 }

hmWanMbus9AValue2E		OBJECT-TYPE
			SYNTAX	INTEGER
			MAX-ACCESS	read-only
			STATUS	current
			::= { hmWanMbus9A 99 }

hmWanMbus9AVIF2F		OBJECT-TYPE
			SYNTAX	INTEGER
			MAX-ACCESS	read-only
			STATUS	current
			::= { hmWanMbus9A 100 }

hmWanMbus9AValue2F		OBJECT-TYPE
			SYNTAX	INTEGER
			MAX-ACCESS	read-only
			STATUS	current
			::= { hmWanMbus9A 101 }

hmWanMbus9B			OBJECT IDENTIFIER ::= { hmWanMbus 155 }

hmWanMbus9BIdNumber		OBJECT-TYPE
			SYNTAX	Gauge32
			MAX-ACCESS	read-only
			STATUS	current
			::= { hmWanMbus9B 1 }

hmWanMbus9BManufacturer	OBJECT-TYPE
			SYNTAX	Gauge32
			MAX-ACCESS	read-only
			STATUS	current
			::= { hmWanMbus9B 2 }

hmWanMbus9BVersion		OBJECT-TYPE
			SYNTAX	Gauge32
			MAX-ACCESS	read-only
			STATUS	current
			::= { hmWanMbus9B 3 }

hmWanMbus9BMedium		OBJECT-TYPE
			SYNTAX	Gauge32
			MAX-ACCESS	read-only
			STATUS	current
			::= { hmWanMbus9B 4 }

hmWanMbus9BStatus		OBJECT-TYPE
			SYNTAX	Gauge32
			MAX-ACCESS	read-only
			STATUS	current
			::= { hmWanMbus9B 5 }

hmWanMbus9BVIF00		OBJECT-TYPE
			SYNTAX	INTEGER
			MAX-ACCESS	read-only
			STATUS	current
			::= { hmWanMbus9B 6 }

hmWanMbus9BValue00		OBJECT-TYPE
			SYNTAX	INTEGER
			MAX-ACCESS	read-only
			STATUS	current
			::= { hmWanMbus9B 7 }

hmWanMbus9BVIF01		OBJECT-TYPE
			SYNTAX	INTEGER
			MAX-ACCESS	read-only
			STATUS	current
			::= { hmWanMbus9B 8 }

hmWanMbus9BValue01		OBJECT-TYPE
			SYNTAX	INTEGER
			MAX-ACCESS	read-only
			STATUS	current
			::= { hmWanMbus9B 9 }

hmWanMbus9BVIF02		OBJECT-TYPE
			SYNTAX	INTEGER
			MAX-ACCESS	read-only
			STATUS	current
			::= { hmWanMbus9B 10 }

hmWanMbus9BValue02		OBJECT-TYPE
			SYNTAX	INTEGER
			MAX-ACCESS	read-only
			STATUS	current
			::= { hmWanMbus9B 11 }

hmWanMbus9BVIF03		OBJECT-TYPE
			SYNTAX	INTEGER
			MAX-ACCESS	read-only
			STATUS	current
			::= { hmWanMbus9B 12 }

hmWanMbus9BValue03		OBJECT-TYPE
			SYNTAX	INTEGER
			MAX-ACCESS	read-only
			STATUS	current
			::= { hmWanMbus9B 13 }

hmWanMbus9BVIF04		OBJECT-TYPE
			SYNTAX	INTEGER
			MAX-ACCESS	read-only
			STATUS	current
			::= { hmWanMbus9B 14 }

hmWanMbus9BValue04		OBJECT-TYPE
			SYNTAX	INTEGER
			MAX-ACCESS	read-only
			STATUS	current
			::= { hmWanMbus9B 15 }

hmWanMbus9BVIF05		OBJECT-TYPE
			SYNTAX	INTEGER
			MAX-ACCESS	read-only
			STATUS	current
			::= { hmWanMbus9B 16 }

hmWanMbus9BValue05		OBJECT-TYPE
			SYNTAX	INTEGER
			MAX-ACCESS	read-only
			STATUS	current
			::= { hmWanMbus9B 17 }

hmWanMbus9BVIF06		OBJECT-TYPE
			SYNTAX	INTEGER
			MAX-ACCESS	read-only
			STATUS	current
			::= { hmWanMbus9B 18 }

hmWanMbus9BValue06		OBJECT-TYPE
			SYNTAX	INTEGER
			MAX-ACCESS	read-only
			STATUS	current
			::= { hmWanMbus9B 19 }

hmWanMbus9BVIF07		OBJECT-TYPE
			SYNTAX	INTEGER
			MAX-ACCESS	read-only
			STATUS	current
			::= { hmWanMbus9B 20 }

hmWanMbus9BValue07		OBJECT-TYPE
			SYNTAX	INTEGER
			MAX-ACCESS	read-only
			STATUS	current
			::= { hmWanMbus9B 21 }

hmWanMbus9BVIF08		OBJECT-TYPE
			SYNTAX	INTEGER
			MAX-ACCESS	read-only
			STATUS	current
			::= { hmWanMbus9B 22 }

hmWanMbus9BValue08		OBJECT-TYPE
			SYNTAX	INTEGER
			MAX-ACCESS	read-only
			STATUS	current
			::= { hmWanMbus9B 23 }

hmWanMbus9BVIF09		OBJECT-TYPE
			SYNTAX	INTEGER
			MAX-ACCESS	read-only
			STATUS	current
			::= { hmWanMbus9B 24 }

hmWanMbus9BValue09		OBJECT-TYPE
			SYNTAX	INTEGER
			MAX-ACCESS	read-only
			STATUS	current
			::= { hmWanMbus9B 25 }

hmWanMbus9BVIF0A		OBJECT-TYPE
			SYNTAX	INTEGER
			MAX-ACCESS	read-only
			STATUS	current
			::= { hmWanMbus9B 26 }

hmWanMbus9BValue0A		OBJECT-TYPE
			SYNTAX	INTEGER
			MAX-ACCESS	read-only
			STATUS	current
			::= { hmWanMbus9B 27 }

hmWanMbus9BVIF0B		OBJECT-TYPE
			SYNTAX	INTEGER
			MAX-ACCESS	read-only
			STATUS	current
			::= { hmWanMbus9B 28 }

hmWanMbus9BValue0B		OBJECT-TYPE
			SYNTAX	INTEGER
			MAX-ACCESS	read-only
			STATUS	current
			::= { hmWanMbus9B 29 }

hmWanMbus9BVIF0C		OBJECT-TYPE
			SYNTAX	INTEGER
			MAX-ACCESS	read-only
			STATUS	current
			::= { hmWanMbus9B 30 }

hmWanMbus9BValue0C		OBJECT-TYPE
			SYNTAX	INTEGER
			MAX-ACCESS	read-only
			STATUS	current
			::= { hmWanMbus9B 31 }

hmWanMbus9BVIF0D		OBJECT-TYPE
			SYNTAX	INTEGER
			MAX-ACCESS	read-only
			STATUS	current
			::= { hmWanMbus9B 32 }

hmWanMbus9BValue0D		OBJECT-TYPE
			SYNTAX	INTEGER
			MAX-ACCESS	read-only
			STATUS	current
			::= { hmWanMbus9B 33 }

hmWanMbus9BVIF0E		OBJECT-TYPE
			SYNTAX	INTEGER
			MAX-ACCESS	read-only
			STATUS	current
			::= { hmWanMbus9B 34 }

hmWanMbus9BValue0E		OBJECT-TYPE
			SYNTAX	INTEGER
			MAX-ACCESS	read-only
			STATUS	current
			::= { hmWanMbus9B 35 }

hmWanMbus9BVIF0F		OBJECT-TYPE
			SYNTAX	INTEGER
			MAX-ACCESS	read-only
			STATUS	current
			::= { hmWanMbus9B 36 }

hmWanMbus9BValue0F		OBJECT-TYPE
			SYNTAX	INTEGER
			MAX-ACCESS	read-only
			STATUS	current
			::= { hmWanMbus9B 37 }

hmWanMbus9BVIF10		OBJECT-TYPE
			SYNTAX	INTEGER
			MAX-ACCESS	read-only
			STATUS	current
			::= { hmWanMbus9B 38 }

hmWanMbus9BValue10		OBJECT-TYPE
			SYNTAX	INTEGER
			MAX-ACCESS	read-only
			STATUS	current
			::= { hmWanMbus9B 39 }

hmWanMbus9BVIF11		OBJECT-TYPE
			SYNTAX	INTEGER
			MAX-ACCESS	read-only
			STATUS	current
			::= { hmWanMbus9B 40 }

hmWanMbus9BValue11		OBJECT-TYPE
			SYNTAX	INTEGER
			MAX-ACCESS	read-only
			STATUS	current
			::= { hmWanMbus9B 41 }

hmWanMbus9BVIF12		OBJECT-TYPE
			SYNTAX	INTEGER
			MAX-ACCESS	read-only
			STATUS	current
			::= { hmWanMbus9B 42 }

hmWanMbus9BValue12		OBJECT-TYPE
			SYNTAX	INTEGER
			MAX-ACCESS	read-only
			STATUS	current
			::= { hmWanMbus9B 43 }

hmWanMbus9BVIF13		OBJECT-TYPE
			SYNTAX	INTEGER
			MAX-ACCESS	read-only
			STATUS	current
			::= { hmWanMbus9B 44 }

hmWanMbus9BValue13		OBJECT-TYPE
			SYNTAX	INTEGER
			MAX-ACCESS	read-only
			STATUS	current
			::= { hmWanMbus9B 45 }

hmWanMbus9BVIF14		OBJECT-TYPE
			SYNTAX	INTEGER
			MAX-ACCESS	read-only
			STATUS	current
			::= { hmWanMbus9B 46 }

hmWanMbus9BValue14		OBJECT-TYPE
			SYNTAX	INTEGER
			MAX-ACCESS	read-only
			STATUS	current
			::= { hmWanMbus9B 47 }

hmWanMbus9BVIF15		OBJECT-TYPE
			SYNTAX	INTEGER
			MAX-ACCESS	read-only
			STATUS	current
			::= { hmWanMbus9B 48 }

hmWanMbus9BValue15		OBJECT-TYPE
			SYNTAX	INTEGER
			MAX-ACCESS	read-only
			STATUS	current
			::= { hmWanMbus9B 49 }

hmWanMbus9BVIF16		OBJECT-TYPE
			SYNTAX	INTEGER
			MAX-ACCESS	read-only
			STATUS	current
			::= { hmWanMbus9B 50 }

hmWanMbus9BValue16		OBJECT-TYPE
			SYNTAX	INTEGER
			MAX-ACCESS	read-only
			STATUS	current
			::= { hmWanMbus9B 51 }

hmWanMbus9BVIF17		OBJECT-TYPE
			SYNTAX	INTEGER
			MAX-ACCESS	read-only
			STATUS	current
			::= { hmWanMbus9B 52 }

hmWanMbus9BValue17		OBJECT-TYPE
			SYNTAX	INTEGER
			MAX-ACCESS	read-only
			STATUS	current
			::= { hmWanMbus9B 53 }

hmWanMbus9BVIF18		OBJECT-TYPE
			SYNTAX	INTEGER
			MAX-ACCESS	read-only
			STATUS	current
			::= { hmWanMbus9B 54 }

hmWanMbus9BValue18		OBJECT-TYPE
			SYNTAX	INTEGER
			MAX-ACCESS	read-only
			STATUS	current
			::= { hmWanMbus9B 55 }

hmWanMbus9BVIF19		OBJECT-TYPE
			SYNTAX	INTEGER
			MAX-ACCESS	read-only
			STATUS	current
			::= { hmWanMbus9B 56 }

hmWanMbus9BValue19		OBJECT-TYPE
			SYNTAX	INTEGER
			MAX-ACCESS	read-only
			STATUS	current
			::= { hmWanMbus9B 57 }

hmWanMbus9BVIF1A		OBJECT-TYPE
			SYNTAX	INTEGER
			MAX-ACCESS	read-only
			STATUS	current
			::= { hmWanMbus9B 58 }

hmWanMbus9BValue1A		OBJECT-TYPE
			SYNTAX	INTEGER
			MAX-ACCESS	read-only
			STATUS	current
			::= { hmWanMbus9B 59 }

hmWanMbus9BVIF1B		OBJECT-TYPE
			SYNTAX	INTEGER
			MAX-ACCESS	read-only
			STATUS	current
			::= { hmWanMbus9B 60 }

hmWanMbus9BValue1B		OBJECT-TYPE
			SYNTAX	INTEGER
			MAX-ACCESS	read-only
			STATUS	current
			::= { hmWanMbus9B 61 }

hmWanMbus9BVIF1C		OBJECT-TYPE
			SYNTAX	INTEGER
			MAX-ACCESS	read-only
			STATUS	current
			::= { hmWanMbus9B 62 }

hmWanMbus9BValue1C		OBJECT-TYPE
			SYNTAX	INTEGER
			MAX-ACCESS	read-only
			STATUS	current
			::= { hmWanMbus9B 63 }

hmWanMbus9BVIF1D		OBJECT-TYPE
			SYNTAX	INTEGER
			MAX-ACCESS	read-only
			STATUS	current
			::= { hmWanMbus9B 64 }

hmWanMbus9BValue1D		OBJECT-TYPE
			SYNTAX	INTEGER
			MAX-ACCESS	read-only
			STATUS	current
			::= { hmWanMbus9B 65 }

hmWanMbus9BVIF1E		OBJECT-TYPE
			SYNTAX	INTEGER
			MAX-ACCESS	read-only
			STATUS	current
			::= { hmWanMbus9B 66 }

hmWanMbus9BValue1E		OBJECT-TYPE
			SYNTAX	INTEGER
			MAX-ACCESS	read-only
			STATUS	current
			::= { hmWanMbus9B 67 }

hmWanMbus9BVIF1F		OBJECT-TYPE
			SYNTAX	INTEGER
			MAX-ACCESS	read-only
			STATUS	current
			::= { hmWanMbus9B 68 }

hmWanMbus9BValue1F		OBJECT-TYPE
			SYNTAX	INTEGER
			MAX-ACCESS	read-only
			STATUS	current
			::= { hmWanMbus9B 69 }

hmWanMbus9BVIF20		OBJECT-TYPE
			SYNTAX	INTEGER
			MAX-ACCESS	read-only
			STATUS	current
			::= { hmWanMbus9B 70 }

hmWanMbus9BValue20		OBJECT-TYPE
			SYNTAX	INTEGER
			MAX-ACCESS	read-only
			STATUS	current
			::= { hmWanMbus9B 71 }

hmWanMbus9BVIF21		OBJECT-TYPE
			SYNTAX	INTEGER
			MAX-ACCESS	read-only
			STATUS	current
			::= { hmWanMbus9B 72 }

hmWanMbus9BValue21		OBJECT-TYPE
			SYNTAX	INTEGER
			MAX-ACCESS	read-only
			STATUS	current
			::= { hmWanMbus9B 73 }

hmWanMbus9BVIF22		OBJECT-TYPE
			SYNTAX	INTEGER
			MAX-ACCESS	read-only
			STATUS	current
			::= { hmWanMbus9B 74 }

hmWanMbus9BValue22		OBJECT-TYPE
			SYNTAX	INTEGER
			MAX-ACCESS	read-only
			STATUS	current
			::= { hmWanMbus9B 75 }

hmWanMbus9BVIF23		OBJECT-TYPE
			SYNTAX	INTEGER
			MAX-ACCESS	read-only
			STATUS	current
			::= { hmWanMbus9B 76 }

hmWanMbus9BValue23		OBJECT-TYPE
			SYNTAX	INTEGER
			MAX-ACCESS	read-only
			STATUS	current
			::= { hmWanMbus9B 77 }

hmWanMbus9BVIF24		OBJECT-TYPE
			SYNTAX	INTEGER
			MAX-ACCESS	read-only
			STATUS	current
			::= { hmWanMbus9B 78 }

hmWanMbus9BValue24		OBJECT-TYPE
			SYNTAX	INTEGER
			MAX-ACCESS	read-only
			STATUS	current
			::= { hmWanMbus9B 79 }

hmWanMbus9BVIF25		OBJECT-TYPE
			SYNTAX	INTEGER
			MAX-ACCESS	read-only
			STATUS	current
			::= { hmWanMbus9B 80 }

hmWanMbus9BValue25		OBJECT-TYPE
			SYNTAX	INTEGER
			MAX-ACCESS	read-only
			STATUS	current
			::= { hmWanMbus9B 81 }

hmWanMbus9BVIF26		OBJECT-TYPE
			SYNTAX	INTEGER
			MAX-ACCESS	read-only
			STATUS	current
			::= { hmWanMbus9B 82 }

hmWanMbus9BValue26		OBJECT-TYPE
			SYNTAX	INTEGER
			MAX-ACCESS	read-only
			STATUS	current
			::= { hmWanMbus9B 83 }

hmWanMbus9BVIF27		OBJECT-TYPE
			SYNTAX	INTEGER
			MAX-ACCESS	read-only
			STATUS	current
			::= { hmWanMbus9B 84 }

hmWanMbus9BValue27		OBJECT-TYPE
			SYNTAX	INTEGER
			MAX-ACCESS	read-only
			STATUS	current
			::= { hmWanMbus9B 85 }

hmWanMbus9BVIF28		OBJECT-TYPE
			SYNTAX	INTEGER
			MAX-ACCESS	read-only
			STATUS	current
			::= { hmWanMbus9B 86 }

hmWanMbus9BValue28		OBJECT-TYPE
			SYNTAX	INTEGER
			MAX-ACCESS	read-only
			STATUS	current
			::= { hmWanMbus9B 87 }

hmWanMbus9BVIF29		OBJECT-TYPE
			SYNTAX	INTEGER
			MAX-ACCESS	read-only
			STATUS	current
			::= { hmWanMbus9B 88 }

hmWanMbus9BValue29		OBJECT-TYPE
			SYNTAX	INTEGER
			MAX-ACCESS	read-only
			STATUS	current
			::= { hmWanMbus9B 89 }

hmWanMbus9BVIF2A		OBJECT-TYPE
			SYNTAX	INTEGER
			MAX-ACCESS	read-only
			STATUS	current
			::= { hmWanMbus9B 90 }

hmWanMbus9BValue2A		OBJECT-TYPE
			SYNTAX	INTEGER
			MAX-ACCESS	read-only
			STATUS	current
			::= { hmWanMbus9B 91 }

hmWanMbus9BVIF2B		OBJECT-TYPE
			SYNTAX	INTEGER
			MAX-ACCESS	read-only
			STATUS	current
			::= { hmWanMbus9B 92 }

hmWanMbus9BValue2B		OBJECT-TYPE
			SYNTAX	INTEGER
			MAX-ACCESS	read-only
			STATUS	current
			::= { hmWanMbus9B 93 }

hmWanMbus9BVIF2C		OBJECT-TYPE
			SYNTAX	INTEGER
			MAX-ACCESS	read-only
			STATUS	current
			::= { hmWanMbus9B 94 }

hmWanMbus9BValue2C		OBJECT-TYPE
			SYNTAX	INTEGER
			MAX-ACCESS	read-only
			STATUS	current
			::= { hmWanMbus9B 95 }

hmWanMbus9BVIF2D		OBJECT-TYPE
			SYNTAX	INTEGER
			MAX-ACCESS	read-only
			STATUS	current
			::= { hmWanMbus9B 96 }

hmWanMbus9BValue2D		OBJECT-TYPE
			SYNTAX	INTEGER
			MAX-ACCESS	read-only
			STATUS	current
			::= { hmWanMbus9B 97 }

hmWanMbus9BVIF2E		OBJECT-TYPE
			SYNTAX	INTEGER
			MAX-ACCESS	read-only
			STATUS	current
			::= { hmWanMbus9B 98 }

hmWanMbus9BValue2E		OBJECT-TYPE
			SYNTAX	INTEGER
			MAX-ACCESS	read-only
			STATUS	current
			::= { hmWanMbus9B 99 }

hmWanMbus9BVIF2F		OBJECT-TYPE
			SYNTAX	INTEGER
			MAX-ACCESS	read-only
			STATUS	current
			::= { hmWanMbus9B 100 }

hmWanMbus9BValue2F		OBJECT-TYPE
			SYNTAX	INTEGER
			MAX-ACCESS	read-only
			STATUS	current
			::= { hmWanMbus9B 101 }

hmWanMbus9C			OBJECT IDENTIFIER ::= { hmWanMbus 156 }

hmWanMbus9CIdNumber		OBJECT-TYPE
			SYNTAX	Gauge32
			MAX-ACCESS	read-only
			STATUS	current
			::= { hmWanMbus9C 1 }

hmWanMbus9CManufacturer	OBJECT-TYPE
			SYNTAX	Gauge32
			MAX-ACCESS	read-only
			STATUS	current
			::= { hmWanMbus9C 2 }

hmWanMbus9CVersion		OBJECT-TYPE
			SYNTAX	Gauge32
			MAX-ACCESS	read-only
			STATUS	current
			::= { hmWanMbus9C 3 }

hmWanMbus9CMedium		OBJECT-TYPE
			SYNTAX	Gauge32
			MAX-ACCESS	read-only
			STATUS	current
			::= { hmWanMbus9C 4 }

hmWanMbus9CStatus		OBJECT-TYPE
			SYNTAX	Gauge32
			MAX-ACCESS	read-only
			STATUS	current
			::= { hmWanMbus9C 5 }

hmWanMbus9CVIF00		OBJECT-TYPE
			SYNTAX	INTEGER
			MAX-ACCESS	read-only
			STATUS	current
			::= { hmWanMbus9C 6 }

hmWanMbus9CValue00		OBJECT-TYPE
			SYNTAX	INTEGER
			MAX-ACCESS	read-only
			STATUS	current
			::= { hmWanMbus9C 7 }

hmWanMbus9CVIF01		OBJECT-TYPE
			SYNTAX	INTEGER
			MAX-ACCESS	read-only
			STATUS	current
			::= { hmWanMbus9C 8 }

hmWanMbus9CValue01		OBJECT-TYPE
			SYNTAX	INTEGER
			MAX-ACCESS	read-only
			STATUS	current
			::= { hmWanMbus9C 9 }

hmWanMbus9CVIF02		OBJECT-TYPE
			SYNTAX	INTEGER
			MAX-ACCESS	read-only
			STATUS	current
			::= { hmWanMbus9C 10 }

hmWanMbus9CValue02		OBJECT-TYPE
			SYNTAX	INTEGER
			MAX-ACCESS	read-only
			STATUS	current
			::= { hmWanMbus9C 11 }

hmWanMbus9CVIF03		OBJECT-TYPE
			SYNTAX	INTEGER
			MAX-ACCESS	read-only
			STATUS	current
			::= { hmWanMbus9C 12 }

hmWanMbus9CValue03		OBJECT-TYPE
			SYNTAX	INTEGER
			MAX-ACCESS	read-only
			STATUS	current
			::= { hmWanMbus9C 13 }

hmWanMbus9CVIF04		OBJECT-TYPE
			SYNTAX	INTEGER
			MAX-ACCESS	read-only
			STATUS	current
			::= { hmWanMbus9C 14 }

hmWanMbus9CValue04		OBJECT-TYPE
			SYNTAX	INTEGER
			MAX-ACCESS	read-only
			STATUS	current
			::= { hmWanMbus9C 15 }

hmWanMbus9CVIF05		OBJECT-TYPE
			SYNTAX	INTEGER
			MAX-ACCESS	read-only
			STATUS	current
			::= { hmWanMbus9C 16 }

hmWanMbus9CValue05		OBJECT-TYPE
			SYNTAX	INTEGER
			MAX-ACCESS	read-only
			STATUS	current
			::= { hmWanMbus9C 17 }

hmWanMbus9CVIF06		OBJECT-TYPE
			SYNTAX	INTEGER
			MAX-ACCESS	read-only
			STATUS	current
			::= { hmWanMbus9C 18 }

hmWanMbus9CValue06		OBJECT-TYPE
			SYNTAX	INTEGER
			MAX-ACCESS	read-only
			STATUS	current
			::= { hmWanMbus9C 19 }

hmWanMbus9CVIF07		OBJECT-TYPE
			SYNTAX	INTEGER
			MAX-ACCESS	read-only
			STATUS	current
			::= { hmWanMbus9C 20 }

hmWanMbus9CValue07		OBJECT-TYPE
			SYNTAX	INTEGER
			MAX-ACCESS	read-only
			STATUS	current
			::= { hmWanMbus9C 21 }

hmWanMbus9CVIF08		OBJECT-TYPE
			SYNTAX	INTEGER
			MAX-ACCESS	read-only
			STATUS	current
			::= { hmWanMbus9C 22 }

hmWanMbus9CValue08		OBJECT-TYPE
			SYNTAX	INTEGER
			MAX-ACCESS	read-only
			STATUS	current
			::= { hmWanMbus9C 23 }

hmWanMbus9CVIF09		OBJECT-TYPE
			SYNTAX	INTEGER
			MAX-ACCESS	read-only
			STATUS	current
			::= { hmWanMbus9C 24 }

hmWanMbus9CValue09		OBJECT-TYPE
			SYNTAX	INTEGER
			MAX-ACCESS	read-only
			STATUS	current
			::= { hmWanMbus9C 25 }

hmWanMbus9CVIF0A		OBJECT-TYPE
			SYNTAX	INTEGER
			MAX-ACCESS	read-only
			STATUS	current
			::= { hmWanMbus9C 26 }

hmWanMbus9CValue0A		OBJECT-TYPE
			SYNTAX	INTEGER
			MAX-ACCESS	read-only
			STATUS	current
			::= { hmWanMbus9C 27 }

hmWanMbus9CVIF0B		OBJECT-TYPE
			SYNTAX	INTEGER
			MAX-ACCESS	read-only
			STATUS	current
			::= { hmWanMbus9C 28 }

hmWanMbus9CValue0B		OBJECT-TYPE
			SYNTAX	INTEGER
			MAX-ACCESS	read-only
			STATUS	current
			::= { hmWanMbus9C 29 }

hmWanMbus9CVIF0C		OBJECT-TYPE
			SYNTAX	INTEGER
			MAX-ACCESS	read-only
			STATUS	current
			::= { hmWanMbus9C 30 }

hmWanMbus9CValue0C		OBJECT-TYPE
			SYNTAX	INTEGER
			MAX-ACCESS	read-only
			STATUS	current
			::= { hmWanMbus9C 31 }

hmWanMbus9CVIF0D		OBJECT-TYPE
			SYNTAX	INTEGER
			MAX-ACCESS	read-only
			STATUS	current
			::= { hmWanMbus9C 32 }

hmWanMbus9CValue0D		OBJECT-TYPE
			SYNTAX	INTEGER
			MAX-ACCESS	read-only
			STATUS	current
			::= { hmWanMbus9C 33 }

hmWanMbus9CVIF0E		OBJECT-TYPE
			SYNTAX	INTEGER
			MAX-ACCESS	read-only
			STATUS	current
			::= { hmWanMbus9C 34 }

hmWanMbus9CValue0E		OBJECT-TYPE
			SYNTAX	INTEGER
			MAX-ACCESS	read-only
			STATUS	current
			::= { hmWanMbus9C 35 }

hmWanMbus9CVIF0F		OBJECT-TYPE
			SYNTAX	INTEGER
			MAX-ACCESS	read-only
			STATUS	current
			::= { hmWanMbus9C 36 }

hmWanMbus9CValue0F		OBJECT-TYPE
			SYNTAX	INTEGER
			MAX-ACCESS	read-only
			STATUS	current
			::= { hmWanMbus9C 37 }

hmWanMbus9CVIF10		OBJECT-TYPE
			SYNTAX	INTEGER
			MAX-ACCESS	read-only
			STATUS	current
			::= { hmWanMbus9C 38 }

hmWanMbus9CValue10		OBJECT-TYPE
			SYNTAX	INTEGER
			MAX-ACCESS	read-only
			STATUS	current
			::= { hmWanMbus9C 39 }

hmWanMbus9CVIF11		OBJECT-TYPE
			SYNTAX	INTEGER
			MAX-ACCESS	read-only
			STATUS	current
			::= { hmWanMbus9C 40 }

hmWanMbus9CValue11		OBJECT-TYPE
			SYNTAX	INTEGER
			MAX-ACCESS	read-only
			STATUS	current
			::= { hmWanMbus9C 41 }

hmWanMbus9CVIF12		OBJECT-TYPE
			SYNTAX	INTEGER
			MAX-ACCESS	read-only
			STATUS	current
			::= { hmWanMbus9C 42 }

hmWanMbus9CValue12		OBJECT-TYPE
			SYNTAX	INTEGER
			MAX-ACCESS	read-only
			STATUS	current
			::= { hmWanMbus9C 43 }

hmWanMbus9CVIF13		OBJECT-TYPE
			SYNTAX	INTEGER
			MAX-ACCESS	read-only
			STATUS	current
			::= { hmWanMbus9C 44 }

hmWanMbus9CValue13		OBJECT-TYPE
			SYNTAX	INTEGER
			MAX-ACCESS	read-only
			STATUS	current
			::= { hmWanMbus9C 45 }

hmWanMbus9CVIF14		OBJECT-TYPE
			SYNTAX	INTEGER
			MAX-ACCESS	read-only
			STATUS	current
			::= { hmWanMbus9C 46 }

hmWanMbus9CValue14		OBJECT-TYPE
			SYNTAX	INTEGER
			MAX-ACCESS	read-only
			STATUS	current
			::= { hmWanMbus9C 47 }

hmWanMbus9CVIF15		OBJECT-TYPE
			SYNTAX	INTEGER
			MAX-ACCESS	read-only
			STATUS	current
			::= { hmWanMbus9C 48 }

hmWanMbus9CValue15		OBJECT-TYPE
			SYNTAX	INTEGER
			MAX-ACCESS	read-only
			STATUS	current
			::= { hmWanMbus9C 49 }

hmWanMbus9CVIF16		OBJECT-TYPE
			SYNTAX	INTEGER
			MAX-ACCESS	read-only
			STATUS	current
			::= { hmWanMbus9C 50 }

hmWanMbus9CValue16		OBJECT-TYPE
			SYNTAX	INTEGER
			MAX-ACCESS	read-only
			STATUS	current
			::= { hmWanMbus9C 51 }

hmWanMbus9CVIF17		OBJECT-TYPE
			SYNTAX	INTEGER
			MAX-ACCESS	read-only
			STATUS	current
			::= { hmWanMbus9C 52 }

hmWanMbus9CValue17		OBJECT-TYPE
			SYNTAX	INTEGER
			MAX-ACCESS	read-only
			STATUS	current
			::= { hmWanMbus9C 53 }

hmWanMbus9CVIF18		OBJECT-TYPE
			SYNTAX	INTEGER
			MAX-ACCESS	read-only
			STATUS	current
			::= { hmWanMbus9C 54 }

hmWanMbus9CValue18		OBJECT-TYPE
			SYNTAX	INTEGER
			MAX-ACCESS	read-only
			STATUS	current
			::= { hmWanMbus9C 55 }

hmWanMbus9CVIF19		OBJECT-TYPE
			SYNTAX	INTEGER
			MAX-ACCESS	read-only
			STATUS	current
			::= { hmWanMbus9C 56 }

hmWanMbus9CValue19		OBJECT-TYPE
			SYNTAX	INTEGER
			MAX-ACCESS	read-only
			STATUS	current
			::= { hmWanMbus9C 57 }

hmWanMbus9CVIF1A		OBJECT-TYPE
			SYNTAX	INTEGER
			MAX-ACCESS	read-only
			STATUS	current
			::= { hmWanMbus9C 58 }

hmWanMbus9CValue1A		OBJECT-TYPE
			SYNTAX	INTEGER
			MAX-ACCESS	read-only
			STATUS	current
			::= { hmWanMbus9C 59 }

hmWanMbus9CVIF1B		OBJECT-TYPE
			SYNTAX	INTEGER
			MAX-ACCESS	read-only
			STATUS	current
			::= { hmWanMbus9C 60 }

hmWanMbus9CValue1B		OBJECT-TYPE
			SYNTAX	INTEGER
			MAX-ACCESS	read-only
			STATUS	current
			::= { hmWanMbus9C 61 }

hmWanMbus9CVIF1C		OBJECT-TYPE
			SYNTAX	INTEGER
			MAX-ACCESS	read-only
			STATUS	current
			::= { hmWanMbus9C 62 }

hmWanMbus9CValue1C		OBJECT-TYPE
			SYNTAX	INTEGER
			MAX-ACCESS	read-only
			STATUS	current
			::= { hmWanMbus9C 63 }

hmWanMbus9CVIF1D		OBJECT-TYPE
			SYNTAX	INTEGER
			MAX-ACCESS	read-only
			STATUS	current
			::= { hmWanMbus9C 64 }

hmWanMbus9CValue1D		OBJECT-TYPE
			SYNTAX	INTEGER
			MAX-ACCESS	read-only
			STATUS	current
			::= { hmWanMbus9C 65 }

hmWanMbus9CVIF1E		OBJECT-TYPE
			SYNTAX	INTEGER
			MAX-ACCESS	read-only
			STATUS	current
			::= { hmWanMbus9C 66 }

hmWanMbus9CValue1E		OBJECT-TYPE
			SYNTAX	INTEGER
			MAX-ACCESS	read-only
			STATUS	current
			::= { hmWanMbus9C 67 }

hmWanMbus9CVIF1F		OBJECT-TYPE
			SYNTAX	INTEGER
			MAX-ACCESS	read-only
			STATUS	current
			::= { hmWanMbus9C 68 }

hmWanMbus9CValue1F		OBJECT-TYPE
			SYNTAX	INTEGER
			MAX-ACCESS	read-only
			STATUS	current
			::= { hmWanMbus9C 69 }

hmWanMbus9CVIF20		OBJECT-TYPE
			SYNTAX	INTEGER
			MAX-ACCESS	read-only
			STATUS	current
			::= { hmWanMbus9C 70 }

hmWanMbus9CValue20		OBJECT-TYPE
			SYNTAX	INTEGER
			MAX-ACCESS	read-only
			STATUS	current
			::= { hmWanMbus9C 71 }

hmWanMbus9CVIF21		OBJECT-TYPE
			SYNTAX	INTEGER
			MAX-ACCESS	read-only
			STATUS	current
			::= { hmWanMbus9C 72 }

hmWanMbus9CValue21		OBJECT-TYPE
			SYNTAX	INTEGER
			MAX-ACCESS	read-only
			STATUS	current
			::= { hmWanMbus9C 73 }

hmWanMbus9CVIF22		OBJECT-TYPE
			SYNTAX	INTEGER
			MAX-ACCESS	read-only
			STATUS	current
			::= { hmWanMbus9C 74 }

hmWanMbus9CValue22		OBJECT-TYPE
			SYNTAX	INTEGER
			MAX-ACCESS	read-only
			STATUS	current
			::= { hmWanMbus9C 75 }

hmWanMbus9CVIF23		OBJECT-TYPE
			SYNTAX	INTEGER
			MAX-ACCESS	read-only
			STATUS	current
			::= { hmWanMbus9C 76 }

hmWanMbus9CValue23		OBJECT-TYPE
			SYNTAX	INTEGER
			MAX-ACCESS	read-only
			STATUS	current
			::= { hmWanMbus9C 77 }

hmWanMbus9CVIF24		OBJECT-TYPE
			SYNTAX	INTEGER
			MAX-ACCESS	read-only
			STATUS	current
			::= { hmWanMbus9C 78 }

hmWanMbus9CValue24		OBJECT-TYPE
			SYNTAX	INTEGER
			MAX-ACCESS	read-only
			STATUS	current
			::= { hmWanMbus9C 79 }

hmWanMbus9CVIF25		OBJECT-TYPE
			SYNTAX	INTEGER
			MAX-ACCESS	read-only
			STATUS	current
			::= { hmWanMbus9C 80 }

hmWanMbus9CValue25		OBJECT-TYPE
			SYNTAX	INTEGER
			MAX-ACCESS	read-only
			STATUS	current
			::= { hmWanMbus9C 81 }

hmWanMbus9CVIF26		OBJECT-TYPE
			SYNTAX	INTEGER
			MAX-ACCESS	read-only
			STATUS	current
			::= { hmWanMbus9C 82 }

hmWanMbus9CValue26		OBJECT-TYPE
			SYNTAX	INTEGER
			MAX-ACCESS	read-only
			STATUS	current
			::= { hmWanMbus9C 83 }

hmWanMbus9CVIF27		OBJECT-TYPE
			SYNTAX	INTEGER
			MAX-ACCESS	read-only
			STATUS	current
			::= { hmWanMbus9C 84 }

hmWanMbus9CValue27		OBJECT-TYPE
			SYNTAX	INTEGER
			MAX-ACCESS	read-only
			STATUS	current
			::= { hmWanMbus9C 85 }

hmWanMbus9CVIF28		OBJECT-TYPE
			SYNTAX	INTEGER
			MAX-ACCESS	read-only
			STATUS	current
			::= { hmWanMbus9C 86 }

hmWanMbus9CValue28		OBJECT-TYPE
			SYNTAX	INTEGER
			MAX-ACCESS	read-only
			STATUS	current
			::= { hmWanMbus9C 87 }

hmWanMbus9CVIF29		OBJECT-TYPE
			SYNTAX	INTEGER
			MAX-ACCESS	read-only
			STATUS	current
			::= { hmWanMbus9C 88 }

hmWanMbus9CValue29		OBJECT-TYPE
			SYNTAX	INTEGER
			MAX-ACCESS	read-only
			STATUS	current
			::= { hmWanMbus9C 89 }

hmWanMbus9CVIF2A		OBJECT-TYPE
			SYNTAX	INTEGER
			MAX-ACCESS	read-only
			STATUS	current
			::= { hmWanMbus9C 90 }

hmWanMbus9CValue2A		OBJECT-TYPE
			SYNTAX	INTEGER
			MAX-ACCESS	read-only
			STATUS	current
			::= { hmWanMbus9C 91 }

hmWanMbus9CVIF2B		OBJECT-TYPE
			SYNTAX	INTEGER
			MAX-ACCESS	read-only
			STATUS	current
			::= { hmWanMbus9C 92 }

hmWanMbus9CValue2B		OBJECT-TYPE
			SYNTAX	INTEGER
			MAX-ACCESS	read-only
			STATUS	current
			::= { hmWanMbus9C 93 }

hmWanMbus9CVIF2C		OBJECT-TYPE
			SYNTAX	INTEGER
			MAX-ACCESS	read-only
			STATUS	current
			::= { hmWanMbus9C 94 }

hmWanMbus9CValue2C		OBJECT-TYPE
			SYNTAX	INTEGER
			MAX-ACCESS	read-only
			STATUS	current
			::= { hmWanMbus9C 95 }

hmWanMbus9CVIF2D		OBJECT-TYPE
			SYNTAX	INTEGER
			MAX-ACCESS	read-only
			STATUS	current
			::= { hmWanMbus9C 96 }

hmWanMbus9CValue2D		OBJECT-TYPE
			SYNTAX	INTEGER
			MAX-ACCESS	read-only
			STATUS	current
			::= { hmWanMbus9C 97 }

hmWanMbus9CVIF2E		OBJECT-TYPE
			SYNTAX	INTEGER
			MAX-ACCESS	read-only
			STATUS	current
			::= { hmWanMbus9C 98 }

hmWanMbus9CValue2E		OBJECT-TYPE
			SYNTAX	INTEGER
			MAX-ACCESS	read-only
			STATUS	current
			::= { hmWanMbus9C 99 }

hmWanMbus9CVIF2F		OBJECT-TYPE
			SYNTAX	INTEGER
			MAX-ACCESS	read-only
			STATUS	current
			::= { hmWanMbus9C 100 }

hmWanMbus9CValue2F		OBJECT-TYPE
			SYNTAX	INTEGER
			MAX-ACCESS	read-only
			STATUS	current
			::= { hmWanMbus9C 101 }

hmWanMbus9D			OBJECT IDENTIFIER ::= { hmWanMbus 157 }

hmWanMbus9DIdNumber		OBJECT-TYPE
			SYNTAX	Gauge32
			MAX-ACCESS	read-only
			STATUS	current
			::= { hmWanMbus9D 1 }

hmWanMbus9DManufacturer	OBJECT-TYPE
			SYNTAX	Gauge32
			MAX-ACCESS	read-only
			STATUS	current
			::= { hmWanMbus9D 2 }

hmWanMbus9DVersion		OBJECT-TYPE
			SYNTAX	Gauge32
			MAX-ACCESS	read-only
			STATUS	current
			::= { hmWanMbus9D 3 }

hmWanMbus9DMedium		OBJECT-TYPE
			SYNTAX	Gauge32
			MAX-ACCESS	read-only
			STATUS	current
			::= { hmWanMbus9D 4 }

hmWanMbus9DStatus		OBJECT-TYPE
			SYNTAX	Gauge32
			MAX-ACCESS	read-only
			STATUS	current
			::= { hmWanMbus9D 5 }

hmWanMbus9DVIF00		OBJECT-TYPE
			SYNTAX	INTEGER
			MAX-ACCESS	read-only
			STATUS	current
			::= { hmWanMbus9D 6 }

hmWanMbus9DValue00		OBJECT-TYPE
			SYNTAX	INTEGER
			MAX-ACCESS	read-only
			STATUS	current
			::= { hmWanMbus9D 7 }

hmWanMbus9DVIF01		OBJECT-TYPE
			SYNTAX	INTEGER
			MAX-ACCESS	read-only
			STATUS	current
			::= { hmWanMbus9D 8 }

hmWanMbus9DValue01		OBJECT-TYPE
			SYNTAX	INTEGER
			MAX-ACCESS	read-only
			STATUS	current
			::= { hmWanMbus9D 9 }

hmWanMbus9DVIF02		OBJECT-TYPE
			SYNTAX	INTEGER
			MAX-ACCESS	read-only
			STATUS	current
			::= { hmWanMbus9D 10 }

hmWanMbus9DValue02		OBJECT-TYPE
			SYNTAX	INTEGER
			MAX-ACCESS	read-only
			STATUS	current
			::= { hmWanMbus9D 11 }

hmWanMbus9DVIF03		OBJECT-TYPE
			SYNTAX	INTEGER
			MAX-ACCESS	read-only
			STATUS	current
			::= { hmWanMbus9D 12 }

hmWanMbus9DValue03		OBJECT-TYPE
			SYNTAX	INTEGER
			MAX-ACCESS	read-only
			STATUS	current
			::= { hmWanMbus9D 13 }

hmWanMbus9DVIF04		OBJECT-TYPE
			SYNTAX	INTEGER
			MAX-ACCESS	read-only
			STATUS	current
			::= { hmWanMbus9D 14 }

hmWanMbus9DValue04		OBJECT-TYPE
			SYNTAX	INTEGER
			MAX-ACCESS	read-only
			STATUS	current
			::= { hmWanMbus9D 15 }

hmWanMbus9DVIF05		OBJECT-TYPE
			SYNTAX	INTEGER
			MAX-ACCESS	read-only
			STATUS	current
			::= { hmWanMbus9D 16 }

hmWanMbus9DValue05		OBJECT-TYPE
			SYNTAX	INTEGER
			MAX-ACCESS	read-only
			STATUS	current
			::= { hmWanMbus9D 17 }

hmWanMbus9DVIF06		OBJECT-TYPE
			SYNTAX	INTEGER
			MAX-ACCESS	read-only
			STATUS	current
			::= { hmWanMbus9D 18 }

hmWanMbus9DValue06		OBJECT-TYPE
			SYNTAX	INTEGER
			MAX-ACCESS	read-only
			STATUS	current
			::= { hmWanMbus9D 19 }

hmWanMbus9DVIF07		OBJECT-TYPE
			SYNTAX	INTEGER
			MAX-ACCESS	read-only
			STATUS	current
			::= { hmWanMbus9D 20 }

hmWanMbus9DValue07		OBJECT-TYPE
			SYNTAX	INTEGER
			MAX-ACCESS	read-only
			STATUS	current
			::= { hmWanMbus9D 21 }

hmWanMbus9DVIF08		OBJECT-TYPE
			SYNTAX	INTEGER
			MAX-ACCESS	read-only
			STATUS	current
			::= { hmWanMbus9D 22 }

hmWanMbus9DValue08		OBJECT-TYPE
			SYNTAX	INTEGER
			MAX-ACCESS	read-only
			STATUS	current
			::= { hmWanMbus9D 23 }

hmWanMbus9DVIF09		OBJECT-TYPE
			SYNTAX	INTEGER
			MAX-ACCESS	read-only
			STATUS	current
			::= { hmWanMbus9D 24 }

hmWanMbus9DValue09		OBJECT-TYPE
			SYNTAX	INTEGER
			MAX-ACCESS	read-only
			STATUS	current
			::= { hmWanMbus9D 25 }

hmWanMbus9DVIF0A		OBJECT-TYPE
			SYNTAX	INTEGER
			MAX-ACCESS	read-only
			STATUS	current
			::= { hmWanMbus9D 26 }

hmWanMbus9DValue0A		OBJECT-TYPE
			SYNTAX	INTEGER
			MAX-ACCESS	read-only
			STATUS	current
			::= { hmWanMbus9D 27 }

hmWanMbus9DVIF0B		OBJECT-TYPE
			SYNTAX	INTEGER
			MAX-ACCESS	read-only
			STATUS	current
			::= { hmWanMbus9D 28 }

hmWanMbus9DValue0B		OBJECT-TYPE
			SYNTAX	INTEGER
			MAX-ACCESS	read-only
			STATUS	current
			::= { hmWanMbus9D 29 }

hmWanMbus9DVIF0C		OBJECT-TYPE
			SYNTAX	INTEGER
			MAX-ACCESS	read-only
			STATUS	current
			::= { hmWanMbus9D 30 }

hmWanMbus9DValue0C		OBJECT-TYPE
			SYNTAX	INTEGER
			MAX-ACCESS	read-only
			STATUS	current
			::= { hmWanMbus9D 31 }

hmWanMbus9DVIF0D		OBJECT-TYPE
			SYNTAX	INTEGER
			MAX-ACCESS	read-only
			STATUS	current
			::= { hmWanMbus9D 32 }

hmWanMbus9DValue0D		OBJECT-TYPE
			SYNTAX	INTEGER
			MAX-ACCESS	read-only
			STATUS	current
			::= { hmWanMbus9D 33 }

hmWanMbus9DVIF0E		OBJECT-TYPE
			SYNTAX	INTEGER
			MAX-ACCESS	read-only
			STATUS	current
			::= { hmWanMbus9D 34 }

hmWanMbus9DValue0E		OBJECT-TYPE
			SYNTAX	INTEGER
			MAX-ACCESS	read-only
			STATUS	current
			::= { hmWanMbus9D 35 }

hmWanMbus9DVIF0F		OBJECT-TYPE
			SYNTAX	INTEGER
			MAX-ACCESS	read-only
			STATUS	current
			::= { hmWanMbus9D 36 }

hmWanMbus9DValue0F		OBJECT-TYPE
			SYNTAX	INTEGER
			MAX-ACCESS	read-only
			STATUS	current
			::= { hmWanMbus9D 37 }

hmWanMbus9DVIF10		OBJECT-TYPE
			SYNTAX	INTEGER
			MAX-ACCESS	read-only
			STATUS	current
			::= { hmWanMbus9D 38 }

hmWanMbus9DValue10		OBJECT-TYPE
			SYNTAX	INTEGER
			MAX-ACCESS	read-only
			STATUS	current
			::= { hmWanMbus9D 39 }

hmWanMbus9DVIF11		OBJECT-TYPE
			SYNTAX	INTEGER
			MAX-ACCESS	read-only
			STATUS	current
			::= { hmWanMbus9D 40 }

hmWanMbus9DValue11		OBJECT-TYPE
			SYNTAX	INTEGER
			MAX-ACCESS	read-only
			STATUS	current
			::= { hmWanMbus9D 41 }

hmWanMbus9DVIF12		OBJECT-TYPE
			SYNTAX	INTEGER
			MAX-ACCESS	read-only
			STATUS	current
			::= { hmWanMbus9D 42 }

hmWanMbus9DValue12		OBJECT-TYPE
			SYNTAX	INTEGER
			MAX-ACCESS	read-only
			STATUS	current
			::= { hmWanMbus9D 43 }

hmWanMbus9DVIF13		OBJECT-TYPE
			SYNTAX	INTEGER
			MAX-ACCESS	read-only
			STATUS	current
			::= { hmWanMbus9D 44 }

hmWanMbus9DValue13		OBJECT-TYPE
			SYNTAX	INTEGER
			MAX-ACCESS	read-only
			STATUS	current
			::= { hmWanMbus9D 45 }

hmWanMbus9DVIF14		OBJECT-TYPE
			SYNTAX	INTEGER
			MAX-ACCESS	read-only
			STATUS	current
			::= { hmWanMbus9D 46 }

hmWanMbus9DValue14		OBJECT-TYPE
			SYNTAX	INTEGER
			MAX-ACCESS	read-only
			STATUS	current
			::= { hmWanMbus9D 47 }

hmWanMbus9DVIF15		OBJECT-TYPE
			SYNTAX	INTEGER
			MAX-ACCESS	read-only
			STATUS	current
			::= { hmWanMbus9D 48 }

hmWanMbus9DValue15		OBJECT-TYPE
			SYNTAX	INTEGER
			MAX-ACCESS	read-only
			STATUS	current
			::= { hmWanMbus9D 49 }

hmWanMbus9DVIF16		OBJECT-TYPE
			SYNTAX	INTEGER
			MAX-ACCESS	read-only
			STATUS	current
			::= { hmWanMbus9D 50 }

hmWanMbus9DValue16		OBJECT-TYPE
			SYNTAX	INTEGER
			MAX-ACCESS	read-only
			STATUS	current
			::= { hmWanMbus9D 51 }

hmWanMbus9DVIF17		OBJECT-TYPE
			SYNTAX	INTEGER
			MAX-ACCESS	read-only
			STATUS	current
			::= { hmWanMbus9D 52 }

hmWanMbus9DValue17		OBJECT-TYPE
			SYNTAX	INTEGER
			MAX-ACCESS	read-only
			STATUS	current
			::= { hmWanMbus9D 53 }

hmWanMbus9DVIF18		OBJECT-TYPE
			SYNTAX	INTEGER
			MAX-ACCESS	read-only
			STATUS	current
			::= { hmWanMbus9D 54 }

hmWanMbus9DValue18		OBJECT-TYPE
			SYNTAX	INTEGER
			MAX-ACCESS	read-only
			STATUS	current
			::= { hmWanMbus9D 55 }

hmWanMbus9DVIF19		OBJECT-TYPE
			SYNTAX	INTEGER
			MAX-ACCESS	read-only
			STATUS	current
			::= { hmWanMbus9D 56 }

hmWanMbus9DValue19		OBJECT-TYPE
			SYNTAX	INTEGER
			MAX-ACCESS	read-only
			STATUS	current
			::= { hmWanMbus9D 57 }

hmWanMbus9DVIF1A		OBJECT-TYPE
			SYNTAX	INTEGER
			MAX-ACCESS	read-only
			STATUS	current
			::= { hmWanMbus9D 58 }

hmWanMbus9DValue1A		OBJECT-TYPE
			SYNTAX	INTEGER
			MAX-ACCESS	read-only
			STATUS	current
			::= { hmWanMbus9D 59 }

hmWanMbus9DVIF1B		OBJECT-TYPE
			SYNTAX	INTEGER
			MAX-ACCESS	read-only
			STATUS	current
			::= { hmWanMbus9D 60 }

hmWanMbus9DValue1B		OBJECT-TYPE
			SYNTAX	INTEGER
			MAX-ACCESS	read-only
			STATUS	current
			::= { hmWanMbus9D 61 }

hmWanMbus9DVIF1C		OBJECT-TYPE
			SYNTAX	INTEGER
			MAX-ACCESS	read-only
			STATUS	current
			::= { hmWanMbus9D 62 }

hmWanMbus9DValue1C		OBJECT-TYPE
			SYNTAX	INTEGER
			MAX-ACCESS	read-only
			STATUS	current
			::= { hmWanMbus9D 63 }

hmWanMbus9DVIF1D		OBJECT-TYPE
			SYNTAX	INTEGER
			MAX-ACCESS	read-only
			STATUS	current
			::= { hmWanMbus9D 64 }

hmWanMbus9DValue1D		OBJECT-TYPE
			SYNTAX	INTEGER
			MAX-ACCESS	read-only
			STATUS	current
			::= { hmWanMbus9D 65 }

hmWanMbus9DVIF1E		OBJECT-TYPE
			SYNTAX	INTEGER
			MAX-ACCESS	read-only
			STATUS	current
			::= { hmWanMbus9D 66 }

hmWanMbus9DValue1E		OBJECT-TYPE
			SYNTAX	INTEGER
			MAX-ACCESS	read-only
			STATUS	current
			::= { hmWanMbus9D 67 }

hmWanMbus9DVIF1F		OBJECT-TYPE
			SYNTAX	INTEGER
			MAX-ACCESS	read-only
			STATUS	current
			::= { hmWanMbus9D 68 }

hmWanMbus9DValue1F		OBJECT-TYPE
			SYNTAX	INTEGER
			MAX-ACCESS	read-only
			STATUS	current
			::= { hmWanMbus9D 69 }

hmWanMbus9DVIF20		OBJECT-TYPE
			SYNTAX	INTEGER
			MAX-ACCESS	read-only
			STATUS	current
			::= { hmWanMbus9D 70 }

hmWanMbus9DValue20		OBJECT-TYPE
			SYNTAX	INTEGER
			MAX-ACCESS	read-only
			STATUS	current
			::= { hmWanMbus9D 71 }

hmWanMbus9DVIF21		OBJECT-TYPE
			SYNTAX	INTEGER
			MAX-ACCESS	read-only
			STATUS	current
			::= { hmWanMbus9D 72 }

hmWanMbus9DValue21		OBJECT-TYPE
			SYNTAX	INTEGER
			MAX-ACCESS	read-only
			STATUS	current
			::= { hmWanMbus9D 73 }

hmWanMbus9DVIF22		OBJECT-TYPE
			SYNTAX	INTEGER
			MAX-ACCESS	read-only
			STATUS	current
			::= { hmWanMbus9D 74 }

hmWanMbus9DValue22		OBJECT-TYPE
			SYNTAX	INTEGER
			MAX-ACCESS	read-only
			STATUS	current
			::= { hmWanMbus9D 75 }

hmWanMbus9DVIF23		OBJECT-TYPE
			SYNTAX	INTEGER
			MAX-ACCESS	read-only
			STATUS	current
			::= { hmWanMbus9D 76 }

hmWanMbus9DValue23		OBJECT-TYPE
			SYNTAX	INTEGER
			MAX-ACCESS	read-only
			STATUS	current
			::= { hmWanMbus9D 77 }

hmWanMbus9DVIF24		OBJECT-TYPE
			SYNTAX	INTEGER
			MAX-ACCESS	read-only
			STATUS	current
			::= { hmWanMbus9D 78 }

hmWanMbus9DValue24		OBJECT-TYPE
			SYNTAX	INTEGER
			MAX-ACCESS	read-only
			STATUS	current
			::= { hmWanMbus9D 79 }

hmWanMbus9DVIF25		OBJECT-TYPE
			SYNTAX	INTEGER
			MAX-ACCESS	read-only
			STATUS	current
			::= { hmWanMbus9D 80 }

hmWanMbus9DValue25		OBJECT-TYPE
			SYNTAX	INTEGER
			MAX-ACCESS	read-only
			STATUS	current
			::= { hmWanMbus9D 81 }

hmWanMbus9DVIF26		OBJECT-TYPE
			SYNTAX	INTEGER
			MAX-ACCESS	read-only
			STATUS	current
			::= { hmWanMbus9D 82 }

hmWanMbus9DValue26		OBJECT-TYPE
			SYNTAX	INTEGER
			MAX-ACCESS	read-only
			STATUS	current
			::= { hmWanMbus9D 83 }

hmWanMbus9DVIF27		OBJECT-TYPE
			SYNTAX	INTEGER
			MAX-ACCESS	read-only
			STATUS	current
			::= { hmWanMbus9D 84 }

hmWanMbus9DValue27		OBJECT-TYPE
			SYNTAX	INTEGER
			MAX-ACCESS	read-only
			STATUS	current
			::= { hmWanMbus9D 85 }

hmWanMbus9DVIF28		OBJECT-TYPE
			SYNTAX	INTEGER
			MAX-ACCESS	read-only
			STATUS	current
			::= { hmWanMbus9D 86 }

hmWanMbus9DValue28		OBJECT-TYPE
			SYNTAX	INTEGER
			MAX-ACCESS	read-only
			STATUS	current
			::= { hmWanMbus9D 87 }

hmWanMbus9DVIF29		OBJECT-TYPE
			SYNTAX	INTEGER
			MAX-ACCESS	read-only
			STATUS	current
			::= { hmWanMbus9D 88 }

hmWanMbus9DValue29		OBJECT-TYPE
			SYNTAX	INTEGER
			MAX-ACCESS	read-only
			STATUS	current
			::= { hmWanMbus9D 89 }

hmWanMbus9DVIF2A		OBJECT-TYPE
			SYNTAX	INTEGER
			MAX-ACCESS	read-only
			STATUS	current
			::= { hmWanMbus9D 90 }

hmWanMbus9DValue2A		OBJECT-TYPE
			SYNTAX	INTEGER
			MAX-ACCESS	read-only
			STATUS	current
			::= { hmWanMbus9D 91 }

hmWanMbus9DVIF2B		OBJECT-TYPE
			SYNTAX	INTEGER
			MAX-ACCESS	read-only
			STATUS	current
			::= { hmWanMbus9D 92 }

hmWanMbus9DValue2B		OBJECT-TYPE
			SYNTAX	INTEGER
			MAX-ACCESS	read-only
			STATUS	current
			::= { hmWanMbus9D 93 }

hmWanMbus9DVIF2C		OBJECT-TYPE
			SYNTAX	INTEGER
			MAX-ACCESS	read-only
			STATUS	current
			::= { hmWanMbus9D 94 }

hmWanMbus9DValue2C		OBJECT-TYPE
			SYNTAX	INTEGER
			MAX-ACCESS	read-only
			STATUS	current
			::= { hmWanMbus9D 95 }

hmWanMbus9DVIF2D		OBJECT-TYPE
			SYNTAX	INTEGER
			MAX-ACCESS	read-only
			STATUS	current
			::= { hmWanMbus9D 96 }

hmWanMbus9DValue2D		OBJECT-TYPE
			SYNTAX	INTEGER
			MAX-ACCESS	read-only
			STATUS	current
			::= { hmWanMbus9D 97 }

hmWanMbus9DVIF2E		OBJECT-TYPE
			SYNTAX	INTEGER
			MAX-ACCESS	read-only
			STATUS	current
			::= { hmWanMbus9D 98 }

hmWanMbus9DValue2E		OBJECT-TYPE
			SYNTAX	INTEGER
			MAX-ACCESS	read-only
			STATUS	current
			::= { hmWanMbus9D 99 }

hmWanMbus9DVIF2F		OBJECT-TYPE
			SYNTAX	INTEGER
			MAX-ACCESS	read-only
			STATUS	current
			::= { hmWanMbus9D 100 }

hmWanMbus9DValue2F		OBJECT-TYPE
			SYNTAX	INTEGER
			MAX-ACCESS	read-only
			STATUS	current
			::= { hmWanMbus9D 101 }

hmWanMbus9E			OBJECT IDENTIFIER ::= { hmWanMbus 158 }

hmWanMbus9EIdNumber		OBJECT-TYPE
			SYNTAX	Gauge32
			MAX-ACCESS	read-only
			STATUS	current
			::= { hmWanMbus9E 1 }

hmWanMbus9EManufacturer	OBJECT-TYPE
			SYNTAX	Gauge32
			MAX-ACCESS	read-only
			STATUS	current
			::= { hmWanMbus9E 2 }

hmWanMbus9EVersion		OBJECT-TYPE
			SYNTAX	Gauge32
			MAX-ACCESS	read-only
			STATUS	current
			::= { hmWanMbus9E 3 }

hmWanMbus9EMedium		OBJECT-TYPE
			SYNTAX	Gauge32
			MAX-ACCESS	read-only
			STATUS	current
			::= { hmWanMbus9E 4 }

hmWanMbus9EStatus		OBJECT-TYPE
			SYNTAX	Gauge32
			MAX-ACCESS	read-only
			STATUS	current
			::= { hmWanMbus9E 5 }

hmWanMbus9EVIF00		OBJECT-TYPE
			SYNTAX	INTEGER
			MAX-ACCESS	read-only
			STATUS	current
			::= { hmWanMbus9E 6 }

hmWanMbus9EValue00		OBJECT-TYPE
			SYNTAX	INTEGER
			MAX-ACCESS	read-only
			STATUS	current
			::= { hmWanMbus9E 7 }

hmWanMbus9EVIF01		OBJECT-TYPE
			SYNTAX	INTEGER
			MAX-ACCESS	read-only
			STATUS	current
			::= { hmWanMbus9E 8 }

hmWanMbus9EValue01		OBJECT-TYPE
			SYNTAX	INTEGER
			MAX-ACCESS	read-only
			STATUS	current
			::= { hmWanMbus9E 9 }

hmWanMbus9EVIF02		OBJECT-TYPE
			SYNTAX	INTEGER
			MAX-ACCESS	read-only
			STATUS	current
			::= { hmWanMbus9E 10 }

hmWanMbus9EValue02		OBJECT-TYPE
			SYNTAX	INTEGER
			MAX-ACCESS	read-only
			STATUS	current
			::= { hmWanMbus9E 11 }

hmWanMbus9EVIF03		OBJECT-TYPE
			SYNTAX	INTEGER
			MAX-ACCESS	read-only
			STATUS	current
			::= { hmWanMbus9E 12 }

hmWanMbus9EValue03		OBJECT-TYPE
			SYNTAX	INTEGER
			MAX-ACCESS	read-only
			STATUS	current
			::= { hmWanMbus9E 13 }

hmWanMbus9EVIF04		OBJECT-TYPE
			SYNTAX	INTEGER
			MAX-ACCESS	read-only
			STATUS	current
			::= { hmWanMbus9E 14 }

hmWanMbus9EValue04		OBJECT-TYPE
			SYNTAX	INTEGER
			MAX-ACCESS	read-only
			STATUS	current
			::= { hmWanMbus9E 15 }

hmWanMbus9EVIF05		OBJECT-TYPE
			SYNTAX	INTEGER
			MAX-ACCESS	read-only
			STATUS	current
			::= { hmWanMbus9E 16 }

hmWanMbus9EValue05		OBJECT-TYPE
			SYNTAX	INTEGER
			MAX-ACCESS	read-only
			STATUS	current
			::= { hmWanMbus9E 17 }

hmWanMbus9EVIF06		OBJECT-TYPE
			SYNTAX	INTEGER
			MAX-ACCESS	read-only
			STATUS	current
			::= { hmWanMbus9E 18 }

hmWanMbus9EValue06		OBJECT-TYPE
			SYNTAX	INTEGER
			MAX-ACCESS	read-only
			STATUS	current
			::= { hmWanMbus9E 19 }

hmWanMbus9EVIF07		OBJECT-TYPE
			SYNTAX	INTEGER
			MAX-ACCESS	read-only
			STATUS	current
			::= { hmWanMbus9E 20 }

hmWanMbus9EValue07		OBJECT-TYPE
			SYNTAX	INTEGER
			MAX-ACCESS	read-only
			STATUS	current
			::= { hmWanMbus9E 21 }

hmWanMbus9EVIF08		OBJECT-TYPE
			SYNTAX	INTEGER
			MAX-ACCESS	read-only
			STATUS	current
			::= { hmWanMbus9E 22 }

hmWanMbus9EValue08		OBJECT-TYPE
			SYNTAX	INTEGER
			MAX-ACCESS	read-only
			STATUS	current
			::= { hmWanMbus9E 23 }

hmWanMbus9EVIF09		OBJECT-TYPE
			SYNTAX	INTEGER
			MAX-ACCESS	read-only
			STATUS	current
			::= { hmWanMbus9E 24 }

hmWanMbus9EValue09		OBJECT-TYPE
			SYNTAX	INTEGER
			MAX-ACCESS	read-only
			STATUS	current
			::= { hmWanMbus9E 25 }

hmWanMbus9EVIF0A		OBJECT-TYPE
			SYNTAX	INTEGER
			MAX-ACCESS	read-only
			STATUS	current
			::= { hmWanMbus9E 26 }

hmWanMbus9EValue0A		OBJECT-TYPE
			SYNTAX	INTEGER
			MAX-ACCESS	read-only
			STATUS	current
			::= { hmWanMbus9E 27 }

hmWanMbus9EVIF0B		OBJECT-TYPE
			SYNTAX	INTEGER
			MAX-ACCESS	read-only
			STATUS	current
			::= { hmWanMbus9E 28 }

hmWanMbus9EValue0B		OBJECT-TYPE
			SYNTAX	INTEGER
			MAX-ACCESS	read-only
			STATUS	current
			::= { hmWanMbus9E 29 }

hmWanMbus9EVIF0C		OBJECT-TYPE
			SYNTAX	INTEGER
			MAX-ACCESS	read-only
			STATUS	current
			::= { hmWanMbus9E 30 }

hmWanMbus9EValue0C		OBJECT-TYPE
			SYNTAX	INTEGER
			MAX-ACCESS	read-only
			STATUS	current
			::= { hmWanMbus9E 31 }

hmWanMbus9EVIF0D		OBJECT-TYPE
			SYNTAX	INTEGER
			MAX-ACCESS	read-only
			STATUS	current
			::= { hmWanMbus9E 32 }

hmWanMbus9EValue0D		OBJECT-TYPE
			SYNTAX	INTEGER
			MAX-ACCESS	read-only
			STATUS	current
			::= { hmWanMbus9E 33 }

hmWanMbus9EVIF0E		OBJECT-TYPE
			SYNTAX	INTEGER
			MAX-ACCESS	read-only
			STATUS	current
			::= { hmWanMbus9E 34 }

hmWanMbus9EValue0E		OBJECT-TYPE
			SYNTAX	INTEGER
			MAX-ACCESS	read-only
			STATUS	current
			::= { hmWanMbus9E 35 }

hmWanMbus9EVIF0F		OBJECT-TYPE
			SYNTAX	INTEGER
			MAX-ACCESS	read-only
			STATUS	current
			::= { hmWanMbus9E 36 }

hmWanMbus9EValue0F		OBJECT-TYPE
			SYNTAX	INTEGER
			MAX-ACCESS	read-only
			STATUS	current
			::= { hmWanMbus9E 37 }

hmWanMbus9EVIF10		OBJECT-TYPE
			SYNTAX	INTEGER
			MAX-ACCESS	read-only
			STATUS	current
			::= { hmWanMbus9E 38 }

hmWanMbus9EValue10		OBJECT-TYPE
			SYNTAX	INTEGER
			MAX-ACCESS	read-only
			STATUS	current
			::= { hmWanMbus9E 39 }

hmWanMbus9EVIF11		OBJECT-TYPE
			SYNTAX	INTEGER
			MAX-ACCESS	read-only
			STATUS	current
			::= { hmWanMbus9E 40 }

hmWanMbus9EValue11		OBJECT-TYPE
			SYNTAX	INTEGER
			MAX-ACCESS	read-only
			STATUS	current
			::= { hmWanMbus9E 41 }

hmWanMbus9EVIF12		OBJECT-TYPE
			SYNTAX	INTEGER
			MAX-ACCESS	read-only
			STATUS	current
			::= { hmWanMbus9E 42 }

hmWanMbus9EValue12		OBJECT-TYPE
			SYNTAX	INTEGER
			MAX-ACCESS	read-only
			STATUS	current
			::= { hmWanMbus9E 43 }

hmWanMbus9EVIF13		OBJECT-TYPE
			SYNTAX	INTEGER
			MAX-ACCESS	read-only
			STATUS	current
			::= { hmWanMbus9E 44 }

hmWanMbus9EValue13		OBJECT-TYPE
			SYNTAX	INTEGER
			MAX-ACCESS	read-only
			STATUS	current
			::= { hmWanMbus9E 45 }

hmWanMbus9EVIF14		OBJECT-TYPE
			SYNTAX	INTEGER
			MAX-ACCESS	read-only
			STATUS	current
			::= { hmWanMbus9E 46 }

hmWanMbus9EValue14		OBJECT-TYPE
			SYNTAX	INTEGER
			MAX-ACCESS	read-only
			STATUS	current
			::= { hmWanMbus9E 47 }

hmWanMbus9EVIF15		OBJECT-TYPE
			SYNTAX	INTEGER
			MAX-ACCESS	read-only
			STATUS	current
			::= { hmWanMbus9E 48 }

hmWanMbus9EValue15		OBJECT-TYPE
			SYNTAX	INTEGER
			MAX-ACCESS	read-only
			STATUS	current
			::= { hmWanMbus9E 49 }

hmWanMbus9EVIF16		OBJECT-TYPE
			SYNTAX	INTEGER
			MAX-ACCESS	read-only
			STATUS	current
			::= { hmWanMbus9E 50 }

hmWanMbus9EValue16		OBJECT-TYPE
			SYNTAX	INTEGER
			MAX-ACCESS	read-only
			STATUS	current
			::= { hmWanMbus9E 51 }

hmWanMbus9EVIF17		OBJECT-TYPE
			SYNTAX	INTEGER
			MAX-ACCESS	read-only
			STATUS	current
			::= { hmWanMbus9E 52 }

hmWanMbus9EValue17		OBJECT-TYPE
			SYNTAX	INTEGER
			MAX-ACCESS	read-only
			STATUS	current
			::= { hmWanMbus9E 53 }

hmWanMbus9EVIF18		OBJECT-TYPE
			SYNTAX	INTEGER
			MAX-ACCESS	read-only
			STATUS	current
			::= { hmWanMbus9E 54 }

hmWanMbus9EValue18		OBJECT-TYPE
			SYNTAX	INTEGER
			MAX-ACCESS	read-only
			STATUS	current
			::= { hmWanMbus9E 55 }

hmWanMbus9EVIF19		OBJECT-TYPE
			SYNTAX	INTEGER
			MAX-ACCESS	read-only
			STATUS	current
			::= { hmWanMbus9E 56 }

hmWanMbus9EValue19		OBJECT-TYPE
			SYNTAX	INTEGER
			MAX-ACCESS	read-only
			STATUS	current
			::= { hmWanMbus9E 57 }

hmWanMbus9EVIF1A		OBJECT-TYPE
			SYNTAX	INTEGER
			MAX-ACCESS	read-only
			STATUS	current
			::= { hmWanMbus9E 58 }

hmWanMbus9EValue1A		OBJECT-TYPE
			SYNTAX	INTEGER
			MAX-ACCESS	read-only
			STATUS	current
			::= { hmWanMbus9E 59 }

hmWanMbus9EVIF1B		OBJECT-TYPE
			SYNTAX	INTEGER
			MAX-ACCESS	read-only
			STATUS	current
			::= { hmWanMbus9E 60 }

hmWanMbus9EValue1B		OBJECT-TYPE
			SYNTAX	INTEGER
			MAX-ACCESS	read-only
			STATUS	current
			::= { hmWanMbus9E 61 }

hmWanMbus9EVIF1C		OBJECT-TYPE
			SYNTAX	INTEGER
			MAX-ACCESS	read-only
			STATUS	current
			::= { hmWanMbus9E 62 }

hmWanMbus9EValue1C		OBJECT-TYPE
			SYNTAX	INTEGER
			MAX-ACCESS	read-only
			STATUS	current
			::= { hmWanMbus9E 63 }

hmWanMbus9EVIF1D		OBJECT-TYPE
			SYNTAX	INTEGER
			MAX-ACCESS	read-only
			STATUS	current
			::= { hmWanMbus9E 64 }

hmWanMbus9EValue1D		OBJECT-TYPE
			SYNTAX	INTEGER
			MAX-ACCESS	read-only
			STATUS	current
			::= { hmWanMbus9E 65 }

hmWanMbus9EVIF1E		OBJECT-TYPE
			SYNTAX	INTEGER
			MAX-ACCESS	read-only
			STATUS	current
			::= { hmWanMbus9E 66 }

hmWanMbus9EValue1E		OBJECT-TYPE
			SYNTAX	INTEGER
			MAX-ACCESS	read-only
			STATUS	current
			::= { hmWanMbus9E 67 }

hmWanMbus9EVIF1F		OBJECT-TYPE
			SYNTAX	INTEGER
			MAX-ACCESS	read-only
			STATUS	current
			::= { hmWanMbus9E 68 }

hmWanMbus9EValue1F		OBJECT-TYPE
			SYNTAX	INTEGER
			MAX-ACCESS	read-only
			STATUS	current
			::= { hmWanMbus9E 69 }

hmWanMbus9EVIF20		OBJECT-TYPE
			SYNTAX	INTEGER
			MAX-ACCESS	read-only
			STATUS	current
			::= { hmWanMbus9E 70 }

hmWanMbus9EValue20		OBJECT-TYPE
			SYNTAX	INTEGER
			MAX-ACCESS	read-only
			STATUS	current
			::= { hmWanMbus9E 71 }

hmWanMbus9EVIF21		OBJECT-TYPE
			SYNTAX	INTEGER
			MAX-ACCESS	read-only
			STATUS	current
			::= { hmWanMbus9E 72 }

hmWanMbus9EValue21		OBJECT-TYPE
			SYNTAX	INTEGER
			MAX-ACCESS	read-only
			STATUS	current
			::= { hmWanMbus9E 73 }

hmWanMbus9EVIF22		OBJECT-TYPE
			SYNTAX	INTEGER
			MAX-ACCESS	read-only
			STATUS	current
			::= { hmWanMbus9E 74 }

hmWanMbus9EValue22		OBJECT-TYPE
			SYNTAX	INTEGER
			MAX-ACCESS	read-only
			STATUS	current
			::= { hmWanMbus9E 75 }

hmWanMbus9EVIF23		OBJECT-TYPE
			SYNTAX	INTEGER
			MAX-ACCESS	read-only
			STATUS	current
			::= { hmWanMbus9E 76 }

hmWanMbus9EValue23		OBJECT-TYPE
			SYNTAX	INTEGER
			MAX-ACCESS	read-only
			STATUS	current
			::= { hmWanMbus9E 77 }

hmWanMbus9EVIF24		OBJECT-TYPE
			SYNTAX	INTEGER
			MAX-ACCESS	read-only
			STATUS	current
			::= { hmWanMbus9E 78 }

hmWanMbus9EValue24		OBJECT-TYPE
			SYNTAX	INTEGER
			MAX-ACCESS	read-only
			STATUS	current
			::= { hmWanMbus9E 79 }

hmWanMbus9EVIF25		OBJECT-TYPE
			SYNTAX	INTEGER
			MAX-ACCESS	read-only
			STATUS	current
			::= { hmWanMbus9E 80 }

hmWanMbus9EValue25		OBJECT-TYPE
			SYNTAX	INTEGER
			MAX-ACCESS	read-only
			STATUS	current
			::= { hmWanMbus9E 81 }

hmWanMbus9EVIF26		OBJECT-TYPE
			SYNTAX	INTEGER
			MAX-ACCESS	read-only
			STATUS	current
			::= { hmWanMbus9E 82 }

hmWanMbus9EValue26		OBJECT-TYPE
			SYNTAX	INTEGER
			MAX-ACCESS	read-only
			STATUS	current
			::= { hmWanMbus9E 83 }

hmWanMbus9EVIF27		OBJECT-TYPE
			SYNTAX	INTEGER
			MAX-ACCESS	read-only
			STATUS	current
			::= { hmWanMbus9E 84 }

hmWanMbus9EValue27		OBJECT-TYPE
			SYNTAX	INTEGER
			MAX-ACCESS	read-only
			STATUS	current
			::= { hmWanMbus9E 85 }

hmWanMbus9EVIF28		OBJECT-TYPE
			SYNTAX	INTEGER
			MAX-ACCESS	read-only
			STATUS	current
			::= { hmWanMbus9E 86 }

hmWanMbus9EValue28		OBJECT-TYPE
			SYNTAX	INTEGER
			MAX-ACCESS	read-only
			STATUS	current
			::= { hmWanMbus9E 87 }

hmWanMbus9EVIF29		OBJECT-TYPE
			SYNTAX	INTEGER
			MAX-ACCESS	read-only
			STATUS	current
			::= { hmWanMbus9E 88 }

hmWanMbus9EValue29		OBJECT-TYPE
			SYNTAX	INTEGER
			MAX-ACCESS	read-only
			STATUS	current
			::= { hmWanMbus9E 89 }

hmWanMbus9EVIF2A		OBJECT-TYPE
			SYNTAX	INTEGER
			MAX-ACCESS	read-only
			STATUS	current
			::= { hmWanMbus9E 90 }

hmWanMbus9EValue2A		OBJECT-TYPE
			SYNTAX	INTEGER
			MAX-ACCESS	read-only
			STATUS	current
			::= { hmWanMbus9E 91 }

hmWanMbus9EVIF2B		OBJECT-TYPE
			SYNTAX	INTEGER
			MAX-ACCESS	read-only
			STATUS	current
			::= { hmWanMbus9E 92 }

hmWanMbus9EValue2B		OBJECT-TYPE
			SYNTAX	INTEGER
			MAX-ACCESS	read-only
			STATUS	current
			::= { hmWanMbus9E 93 }

hmWanMbus9EVIF2C		OBJECT-TYPE
			SYNTAX	INTEGER
			MAX-ACCESS	read-only
			STATUS	current
			::= { hmWanMbus9E 94 }

hmWanMbus9EValue2C		OBJECT-TYPE
			SYNTAX	INTEGER
			MAX-ACCESS	read-only
			STATUS	current
			::= { hmWanMbus9E 95 }

hmWanMbus9EVIF2D		OBJECT-TYPE
			SYNTAX	INTEGER
			MAX-ACCESS	read-only
			STATUS	current
			::= { hmWanMbus9E 96 }

hmWanMbus9EValue2D		OBJECT-TYPE
			SYNTAX	INTEGER
			MAX-ACCESS	read-only
			STATUS	current
			::= { hmWanMbus9E 97 }

hmWanMbus9EVIF2E		OBJECT-TYPE
			SYNTAX	INTEGER
			MAX-ACCESS	read-only
			STATUS	current
			::= { hmWanMbus9E 98 }

hmWanMbus9EValue2E		OBJECT-TYPE
			SYNTAX	INTEGER
			MAX-ACCESS	read-only
			STATUS	current
			::= { hmWanMbus9E 99 }

hmWanMbus9EVIF2F		OBJECT-TYPE
			SYNTAX	INTEGER
			MAX-ACCESS	read-only
			STATUS	current
			::= { hmWanMbus9E 100 }

hmWanMbus9EValue2F		OBJECT-TYPE
			SYNTAX	INTEGER
			MAX-ACCESS	read-only
			STATUS	current
			::= { hmWanMbus9E 101 }

hmWanMbus9F			OBJECT IDENTIFIER ::= { hmWanMbus 159 }

hmWanMbus9FIdNumber		OBJECT-TYPE
			SYNTAX	Gauge32
			MAX-ACCESS	read-only
			STATUS	current
			::= { hmWanMbus9F 1 }

hmWanMbus9FManufacturer	OBJECT-TYPE
			SYNTAX	Gauge32
			MAX-ACCESS	read-only
			STATUS	current
			::= { hmWanMbus9F 2 }

hmWanMbus9FVersion		OBJECT-TYPE
			SYNTAX	Gauge32
			MAX-ACCESS	read-only
			STATUS	current
			::= { hmWanMbus9F 3 }

hmWanMbus9FMedium		OBJECT-TYPE
			SYNTAX	Gauge32
			MAX-ACCESS	read-only
			STATUS	current
			::= { hmWanMbus9F 4 }

hmWanMbus9FStatus		OBJECT-TYPE
			SYNTAX	Gauge32
			MAX-ACCESS	read-only
			STATUS	current
			::= { hmWanMbus9F 5 }

hmWanMbus9FVIF00		OBJECT-TYPE
			SYNTAX	INTEGER
			MAX-ACCESS	read-only
			STATUS	current
			::= { hmWanMbus9F 6 }

hmWanMbus9FValue00		OBJECT-TYPE
			SYNTAX	INTEGER
			MAX-ACCESS	read-only
			STATUS	current
			::= { hmWanMbus9F 7 }

hmWanMbus9FVIF01		OBJECT-TYPE
			SYNTAX	INTEGER
			MAX-ACCESS	read-only
			STATUS	current
			::= { hmWanMbus9F 8 }

hmWanMbus9FValue01		OBJECT-TYPE
			SYNTAX	INTEGER
			MAX-ACCESS	read-only
			STATUS	current
			::= { hmWanMbus9F 9 }

hmWanMbus9FVIF02		OBJECT-TYPE
			SYNTAX	INTEGER
			MAX-ACCESS	read-only
			STATUS	current
			::= { hmWanMbus9F 10 }

hmWanMbus9FValue02		OBJECT-TYPE
			SYNTAX	INTEGER
			MAX-ACCESS	read-only
			STATUS	current
			::= { hmWanMbus9F 11 }

hmWanMbus9FVIF03		OBJECT-TYPE
			SYNTAX	INTEGER
			MAX-ACCESS	read-only
			STATUS	current
			::= { hmWanMbus9F 12 }

hmWanMbus9FValue03		OBJECT-TYPE
			SYNTAX	INTEGER
			MAX-ACCESS	read-only
			STATUS	current
			::= { hmWanMbus9F 13 }

hmWanMbus9FVIF04		OBJECT-TYPE
			SYNTAX	INTEGER
			MAX-ACCESS	read-only
			STATUS	current
			::= { hmWanMbus9F 14 }

hmWanMbus9FValue04		OBJECT-TYPE
			SYNTAX	INTEGER
			MAX-ACCESS	read-only
			STATUS	current
			::= { hmWanMbus9F 15 }

hmWanMbus9FVIF05		OBJECT-TYPE
			SYNTAX	INTEGER
			MAX-ACCESS	read-only
			STATUS	current
			::= { hmWanMbus9F 16 }

hmWanMbus9FValue05		OBJECT-TYPE
			SYNTAX	INTEGER
			MAX-ACCESS	read-only
			STATUS	current
			::= { hmWanMbus9F 17 }

hmWanMbus9FVIF06		OBJECT-TYPE
			SYNTAX	INTEGER
			MAX-ACCESS	read-only
			STATUS	current
			::= { hmWanMbus9F 18 }

hmWanMbus9FValue06		OBJECT-TYPE
			SYNTAX	INTEGER
			MAX-ACCESS	read-only
			STATUS	current
			::= { hmWanMbus9F 19 }

hmWanMbus9FVIF07		OBJECT-TYPE
			SYNTAX	INTEGER
			MAX-ACCESS	read-only
			STATUS	current
			::= { hmWanMbus9F 20 }

hmWanMbus9FValue07		OBJECT-TYPE
			SYNTAX	INTEGER
			MAX-ACCESS	read-only
			STATUS	current
			::= { hmWanMbus9F 21 }

hmWanMbus9FVIF08		OBJECT-TYPE
			SYNTAX	INTEGER
			MAX-ACCESS	read-only
			STATUS	current
			::= { hmWanMbus9F 22 }

hmWanMbus9FValue08		OBJECT-TYPE
			SYNTAX	INTEGER
			MAX-ACCESS	read-only
			STATUS	current
			::= { hmWanMbus9F 23 }

hmWanMbus9FVIF09		OBJECT-TYPE
			SYNTAX	INTEGER
			MAX-ACCESS	read-only
			STATUS	current
			::= { hmWanMbus9F 24 }

hmWanMbus9FValue09		OBJECT-TYPE
			SYNTAX	INTEGER
			MAX-ACCESS	read-only
			STATUS	current
			::= { hmWanMbus9F 25 }

hmWanMbus9FVIF0A		OBJECT-TYPE
			SYNTAX	INTEGER
			MAX-ACCESS	read-only
			STATUS	current
			::= { hmWanMbus9F 26 }

hmWanMbus9FValue0A		OBJECT-TYPE
			SYNTAX	INTEGER
			MAX-ACCESS	read-only
			STATUS	current
			::= { hmWanMbus9F 27 }

hmWanMbus9FVIF0B		OBJECT-TYPE
			SYNTAX	INTEGER
			MAX-ACCESS	read-only
			STATUS	current
			::= { hmWanMbus9F 28 }

hmWanMbus9FValue0B		OBJECT-TYPE
			SYNTAX	INTEGER
			MAX-ACCESS	read-only
			STATUS	current
			::= { hmWanMbus9F 29 }

hmWanMbus9FVIF0C		OBJECT-TYPE
			SYNTAX	INTEGER
			MAX-ACCESS	read-only
			STATUS	current
			::= { hmWanMbus9F 30 }

hmWanMbus9FValue0C		OBJECT-TYPE
			SYNTAX	INTEGER
			MAX-ACCESS	read-only
			STATUS	current
			::= { hmWanMbus9F 31 }

hmWanMbus9FVIF0D		OBJECT-TYPE
			SYNTAX	INTEGER
			MAX-ACCESS	read-only
			STATUS	current
			::= { hmWanMbus9F 32 }

hmWanMbus9FValue0D		OBJECT-TYPE
			SYNTAX	INTEGER
			MAX-ACCESS	read-only
			STATUS	current
			::= { hmWanMbus9F 33 }

hmWanMbus9FVIF0E		OBJECT-TYPE
			SYNTAX	INTEGER
			MAX-ACCESS	read-only
			STATUS	current
			::= { hmWanMbus9F 34 }

hmWanMbus9FValue0E		OBJECT-TYPE
			SYNTAX	INTEGER
			MAX-ACCESS	read-only
			STATUS	current
			::= { hmWanMbus9F 35 }

hmWanMbus9FVIF0F		OBJECT-TYPE
			SYNTAX	INTEGER
			MAX-ACCESS	read-only
			STATUS	current
			::= { hmWanMbus9F 36 }

hmWanMbus9FValue0F		OBJECT-TYPE
			SYNTAX	INTEGER
			MAX-ACCESS	read-only
			STATUS	current
			::= { hmWanMbus9F 37 }

hmWanMbus9FVIF10		OBJECT-TYPE
			SYNTAX	INTEGER
			MAX-ACCESS	read-only
			STATUS	current
			::= { hmWanMbus9F 38 }

hmWanMbus9FValue10		OBJECT-TYPE
			SYNTAX	INTEGER
			MAX-ACCESS	read-only
			STATUS	current
			::= { hmWanMbus9F 39 }

hmWanMbus9FVIF11		OBJECT-TYPE
			SYNTAX	INTEGER
			MAX-ACCESS	read-only
			STATUS	current
			::= { hmWanMbus9F 40 }

hmWanMbus9FValue11		OBJECT-TYPE
			SYNTAX	INTEGER
			MAX-ACCESS	read-only
			STATUS	current
			::= { hmWanMbus9F 41 }

hmWanMbus9FVIF12		OBJECT-TYPE
			SYNTAX	INTEGER
			MAX-ACCESS	read-only
			STATUS	current
			::= { hmWanMbus9F 42 }

hmWanMbus9FValue12		OBJECT-TYPE
			SYNTAX	INTEGER
			MAX-ACCESS	read-only
			STATUS	current
			::= { hmWanMbus9F 43 }

hmWanMbus9FVIF13		OBJECT-TYPE
			SYNTAX	INTEGER
			MAX-ACCESS	read-only
			STATUS	current
			::= { hmWanMbus9F 44 }

hmWanMbus9FValue13		OBJECT-TYPE
			SYNTAX	INTEGER
			MAX-ACCESS	read-only
			STATUS	current
			::= { hmWanMbus9F 45 }

hmWanMbus9FVIF14		OBJECT-TYPE
			SYNTAX	INTEGER
			MAX-ACCESS	read-only
			STATUS	current
			::= { hmWanMbus9F 46 }

hmWanMbus9FValue14		OBJECT-TYPE
			SYNTAX	INTEGER
			MAX-ACCESS	read-only
			STATUS	current
			::= { hmWanMbus9F 47 }

hmWanMbus9FVIF15		OBJECT-TYPE
			SYNTAX	INTEGER
			MAX-ACCESS	read-only
			STATUS	current
			::= { hmWanMbus9F 48 }

hmWanMbus9FValue15		OBJECT-TYPE
			SYNTAX	INTEGER
			MAX-ACCESS	read-only
			STATUS	current
			::= { hmWanMbus9F 49 }

hmWanMbus9FVIF16		OBJECT-TYPE
			SYNTAX	INTEGER
			MAX-ACCESS	read-only
			STATUS	current
			::= { hmWanMbus9F 50 }

hmWanMbus9FValue16		OBJECT-TYPE
			SYNTAX	INTEGER
			MAX-ACCESS	read-only
			STATUS	current
			::= { hmWanMbus9F 51 }

hmWanMbus9FVIF17		OBJECT-TYPE
			SYNTAX	INTEGER
			MAX-ACCESS	read-only
			STATUS	current
			::= { hmWanMbus9F 52 }

hmWanMbus9FValue17		OBJECT-TYPE
			SYNTAX	INTEGER
			MAX-ACCESS	read-only
			STATUS	current
			::= { hmWanMbus9F 53 }

hmWanMbus9FVIF18		OBJECT-TYPE
			SYNTAX	INTEGER
			MAX-ACCESS	read-only
			STATUS	current
			::= { hmWanMbus9F 54 }

hmWanMbus9FValue18		OBJECT-TYPE
			SYNTAX	INTEGER
			MAX-ACCESS	read-only
			STATUS	current
			::= { hmWanMbus9F 55 }

hmWanMbus9FVIF19		OBJECT-TYPE
			SYNTAX	INTEGER
			MAX-ACCESS	read-only
			STATUS	current
			::= { hmWanMbus9F 56 }

hmWanMbus9FValue19		OBJECT-TYPE
			SYNTAX	INTEGER
			MAX-ACCESS	read-only
			STATUS	current
			::= { hmWanMbus9F 57 }

hmWanMbus9FVIF1A		OBJECT-TYPE
			SYNTAX	INTEGER
			MAX-ACCESS	read-only
			STATUS	current
			::= { hmWanMbus9F 58 }

hmWanMbus9FValue1A		OBJECT-TYPE
			SYNTAX	INTEGER
			MAX-ACCESS	read-only
			STATUS	current
			::= { hmWanMbus9F 59 }

hmWanMbus9FVIF1B		OBJECT-TYPE
			SYNTAX	INTEGER
			MAX-ACCESS	read-only
			STATUS	current
			::= { hmWanMbus9F 60 }

hmWanMbus9FValue1B		OBJECT-TYPE
			SYNTAX	INTEGER
			MAX-ACCESS	read-only
			STATUS	current
			::= { hmWanMbus9F 61 }

hmWanMbus9FVIF1C		OBJECT-TYPE
			SYNTAX	INTEGER
			MAX-ACCESS	read-only
			STATUS	current
			::= { hmWanMbus9F 62 }

hmWanMbus9FValue1C		OBJECT-TYPE
			SYNTAX	INTEGER
			MAX-ACCESS	read-only
			STATUS	current
			::= { hmWanMbus9F 63 }

hmWanMbus9FVIF1D		OBJECT-TYPE
			SYNTAX	INTEGER
			MAX-ACCESS	read-only
			STATUS	current
			::= { hmWanMbus9F 64 }

hmWanMbus9FValue1D		OBJECT-TYPE
			SYNTAX	INTEGER
			MAX-ACCESS	read-only
			STATUS	current
			::= { hmWanMbus9F 65 }

hmWanMbus9FVIF1E		OBJECT-TYPE
			SYNTAX	INTEGER
			MAX-ACCESS	read-only
			STATUS	current
			::= { hmWanMbus9F 66 }

hmWanMbus9FValue1E		OBJECT-TYPE
			SYNTAX	INTEGER
			MAX-ACCESS	read-only
			STATUS	current
			::= { hmWanMbus9F 67 }

hmWanMbus9FVIF1F		OBJECT-TYPE
			SYNTAX	INTEGER
			MAX-ACCESS	read-only
			STATUS	current
			::= { hmWanMbus9F 68 }

hmWanMbus9FValue1F		OBJECT-TYPE
			SYNTAX	INTEGER
			MAX-ACCESS	read-only
			STATUS	current
			::= { hmWanMbus9F 69 }

hmWanMbus9FVIF20		OBJECT-TYPE
			SYNTAX	INTEGER
			MAX-ACCESS	read-only
			STATUS	current
			::= { hmWanMbus9F 70 }

hmWanMbus9FValue20		OBJECT-TYPE
			SYNTAX	INTEGER
			MAX-ACCESS	read-only
			STATUS	current
			::= { hmWanMbus9F 71 }

hmWanMbus9FVIF21		OBJECT-TYPE
			SYNTAX	INTEGER
			MAX-ACCESS	read-only
			STATUS	current
			::= { hmWanMbus9F 72 }

hmWanMbus9FValue21		OBJECT-TYPE
			SYNTAX	INTEGER
			MAX-ACCESS	read-only
			STATUS	current
			::= { hmWanMbus9F 73 }

hmWanMbus9FVIF22		OBJECT-TYPE
			SYNTAX	INTEGER
			MAX-ACCESS	read-only
			STATUS	current
			::= { hmWanMbus9F 74 }

hmWanMbus9FValue22		OBJECT-TYPE
			SYNTAX	INTEGER
			MAX-ACCESS	read-only
			STATUS	current
			::= { hmWanMbus9F 75 }

hmWanMbus9FVIF23		OBJECT-TYPE
			SYNTAX	INTEGER
			MAX-ACCESS	read-only
			STATUS	current
			::= { hmWanMbus9F 76 }

hmWanMbus9FValue23		OBJECT-TYPE
			SYNTAX	INTEGER
			MAX-ACCESS	read-only
			STATUS	current
			::= { hmWanMbus9F 77 }

hmWanMbus9FVIF24		OBJECT-TYPE
			SYNTAX	INTEGER
			MAX-ACCESS	read-only
			STATUS	current
			::= { hmWanMbus9F 78 }

hmWanMbus9FValue24		OBJECT-TYPE
			SYNTAX	INTEGER
			MAX-ACCESS	read-only
			STATUS	current
			::= { hmWanMbus9F 79 }

hmWanMbus9FVIF25		OBJECT-TYPE
			SYNTAX	INTEGER
			MAX-ACCESS	read-only
			STATUS	current
			::= { hmWanMbus9F 80 }

hmWanMbus9FValue25		OBJECT-TYPE
			SYNTAX	INTEGER
			MAX-ACCESS	read-only
			STATUS	current
			::= { hmWanMbus9F 81 }

hmWanMbus9FVIF26		OBJECT-TYPE
			SYNTAX	INTEGER
			MAX-ACCESS	read-only
			STATUS	current
			::= { hmWanMbus9F 82 }

hmWanMbus9FValue26		OBJECT-TYPE
			SYNTAX	INTEGER
			MAX-ACCESS	read-only
			STATUS	current
			::= { hmWanMbus9F 83 }

hmWanMbus9FVIF27		OBJECT-TYPE
			SYNTAX	INTEGER
			MAX-ACCESS	read-only
			STATUS	current
			::= { hmWanMbus9F 84 }

hmWanMbus9FValue27		OBJECT-TYPE
			SYNTAX	INTEGER
			MAX-ACCESS	read-only
			STATUS	current
			::= { hmWanMbus9F 85 }

hmWanMbus9FVIF28		OBJECT-TYPE
			SYNTAX	INTEGER
			MAX-ACCESS	read-only
			STATUS	current
			::= { hmWanMbus9F 86 }

hmWanMbus9FValue28		OBJECT-TYPE
			SYNTAX	INTEGER
			MAX-ACCESS	read-only
			STATUS	current
			::= { hmWanMbus9F 87 }

hmWanMbus9FVIF29		OBJECT-TYPE
			SYNTAX	INTEGER
			MAX-ACCESS	read-only
			STATUS	current
			::= { hmWanMbus9F 88 }

hmWanMbus9FValue29		OBJECT-TYPE
			SYNTAX	INTEGER
			MAX-ACCESS	read-only
			STATUS	current
			::= { hmWanMbus9F 89 }

hmWanMbus9FVIF2A		OBJECT-TYPE
			SYNTAX	INTEGER
			MAX-ACCESS	read-only
			STATUS	current
			::= { hmWanMbus9F 90 }

hmWanMbus9FValue2A		OBJECT-TYPE
			SYNTAX	INTEGER
			MAX-ACCESS	read-only
			STATUS	current
			::= { hmWanMbus9F 91 }

hmWanMbus9FVIF2B		OBJECT-TYPE
			SYNTAX	INTEGER
			MAX-ACCESS	read-only
			STATUS	current
			::= { hmWanMbus9F 92 }

hmWanMbus9FValue2B		OBJECT-TYPE
			SYNTAX	INTEGER
			MAX-ACCESS	read-only
			STATUS	current
			::= { hmWanMbus9F 93 }

hmWanMbus9FVIF2C		OBJECT-TYPE
			SYNTAX	INTEGER
			MAX-ACCESS	read-only
			STATUS	current
			::= { hmWanMbus9F 94 }

hmWanMbus9FValue2C		OBJECT-TYPE
			SYNTAX	INTEGER
			MAX-ACCESS	read-only
			STATUS	current
			::= { hmWanMbus9F 95 }

hmWanMbus9FVIF2D		OBJECT-TYPE
			SYNTAX	INTEGER
			MAX-ACCESS	read-only
			STATUS	current
			::= { hmWanMbus9F 96 }

hmWanMbus9FValue2D		OBJECT-TYPE
			SYNTAX	INTEGER
			MAX-ACCESS	read-only
			STATUS	current
			::= { hmWanMbus9F 97 }

hmWanMbus9FVIF2E		OBJECT-TYPE
			SYNTAX	INTEGER
			MAX-ACCESS	read-only
			STATUS	current
			::= { hmWanMbus9F 98 }

hmWanMbus9FValue2E		OBJECT-TYPE
			SYNTAX	INTEGER
			MAX-ACCESS	read-only
			STATUS	current
			::= { hmWanMbus9F 99 }

hmWanMbus9FVIF2F		OBJECT-TYPE
			SYNTAX	INTEGER
			MAX-ACCESS	read-only
			STATUS	current
			::= { hmWanMbus9F 100 }

hmWanMbus9FValue2F		OBJECT-TYPE
			SYNTAX	INTEGER
			MAX-ACCESS	read-only
			STATUS	current
			::= { hmWanMbus9F 101 }

hmWanMbusA0			OBJECT IDENTIFIER ::= { hmWanMbus 160 }

hmWanMbusA0IdNumber		OBJECT-TYPE
			SYNTAX	Gauge32
			MAX-ACCESS	read-only
			STATUS	current
			::= { hmWanMbusA0 1 }

hmWanMbusA0Manufacturer	OBJECT-TYPE
			SYNTAX	Gauge32
			MAX-ACCESS	read-only
			STATUS	current
			::= { hmWanMbusA0 2 }

hmWanMbusA0Version		OBJECT-TYPE
			SYNTAX	Gauge32
			MAX-ACCESS	read-only
			STATUS	current
			::= { hmWanMbusA0 3 }

hmWanMbusA0Medium		OBJECT-TYPE
			SYNTAX	Gauge32
			MAX-ACCESS	read-only
			STATUS	current
			::= { hmWanMbusA0 4 }

hmWanMbusA0Status		OBJECT-TYPE
			SYNTAX	Gauge32
			MAX-ACCESS	read-only
			STATUS	current
			::= { hmWanMbusA0 5 }

hmWanMbusA0VIF00		OBJECT-TYPE
			SYNTAX	INTEGER
			MAX-ACCESS	read-only
			STATUS	current
			::= { hmWanMbusA0 6 }

hmWanMbusA0Value00		OBJECT-TYPE
			SYNTAX	INTEGER
			MAX-ACCESS	read-only
			STATUS	current
			::= { hmWanMbusA0 7 }

hmWanMbusA0VIF01		OBJECT-TYPE
			SYNTAX	INTEGER
			MAX-ACCESS	read-only
			STATUS	current
			::= { hmWanMbusA0 8 }

hmWanMbusA0Value01		OBJECT-TYPE
			SYNTAX	INTEGER
			MAX-ACCESS	read-only
			STATUS	current
			::= { hmWanMbusA0 9 }

hmWanMbusA0VIF02		OBJECT-TYPE
			SYNTAX	INTEGER
			MAX-ACCESS	read-only
			STATUS	current
			::= { hmWanMbusA0 10 }

hmWanMbusA0Value02		OBJECT-TYPE
			SYNTAX	INTEGER
			MAX-ACCESS	read-only
			STATUS	current
			::= { hmWanMbusA0 11 }

hmWanMbusA0VIF03		OBJECT-TYPE
			SYNTAX	INTEGER
			MAX-ACCESS	read-only
			STATUS	current
			::= { hmWanMbusA0 12 }

hmWanMbusA0Value03		OBJECT-TYPE
			SYNTAX	INTEGER
			MAX-ACCESS	read-only
			STATUS	current
			::= { hmWanMbusA0 13 }

hmWanMbusA0VIF04		OBJECT-TYPE
			SYNTAX	INTEGER
			MAX-ACCESS	read-only
			STATUS	current
			::= { hmWanMbusA0 14 }

hmWanMbusA0Value04		OBJECT-TYPE
			SYNTAX	INTEGER
			MAX-ACCESS	read-only
			STATUS	current
			::= { hmWanMbusA0 15 }

hmWanMbusA0VIF05		OBJECT-TYPE
			SYNTAX	INTEGER
			MAX-ACCESS	read-only
			STATUS	current
			::= { hmWanMbusA0 16 }

hmWanMbusA0Value05		OBJECT-TYPE
			SYNTAX	INTEGER
			MAX-ACCESS	read-only
			STATUS	current
			::= { hmWanMbusA0 17 }

hmWanMbusA0VIF06		OBJECT-TYPE
			SYNTAX	INTEGER
			MAX-ACCESS	read-only
			STATUS	current
			::= { hmWanMbusA0 18 }

hmWanMbusA0Value06		OBJECT-TYPE
			SYNTAX	INTEGER
			MAX-ACCESS	read-only
			STATUS	current
			::= { hmWanMbusA0 19 }

hmWanMbusA0VIF07		OBJECT-TYPE
			SYNTAX	INTEGER
			MAX-ACCESS	read-only
			STATUS	current
			::= { hmWanMbusA0 20 }

hmWanMbusA0Value07		OBJECT-TYPE
			SYNTAX	INTEGER
			MAX-ACCESS	read-only
			STATUS	current
			::= { hmWanMbusA0 21 }

hmWanMbusA0VIF08		OBJECT-TYPE
			SYNTAX	INTEGER
			MAX-ACCESS	read-only
			STATUS	current
			::= { hmWanMbusA0 22 }

hmWanMbusA0Value08		OBJECT-TYPE
			SYNTAX	INTEGER
			MAX-ACCESS	read-only
			STATUS	current
			::= { hmWanMbusA0 23 }

hmWanMbusA0VIF09		OBJECT-TYPE
			SYNTAX	INTEGER
			MAX-ACCESS	read-only
			STATUS	current
			::= { hmWanMbusA0 24 }

hmWanMbusA0Value09		OBJECT-TYPE
			SYNTAX	INTEGER
			MAX-ACCESS	read-only
			STATUS	current
			::= { hmWanMbusA0 25 }

hmWanMbusA0VIF0A		OBJECT-TYPE
			SYNTAX	INTEGER
			MAX-ACCESS	read-only
			STATUS	current
			::= { hmWanMbusA0 26 }

hmWanMbusA0Value0A		OBJECT-TYPE
			SYNTAX	INTEGER
			MAX-ACCESS	read-only
			STATUS	current
			::= { hmWanMbusA0 27 }

hmWanMbusA0VIF0B		OBJECT-TYPE
			SYNTAX	INTEGER
			MAX-ACCESS	read-only
			STATUS	current
			::= { hmWanMbusA0 28 }

hmWanMbusA0Value0B		OBJECT-TYPE
			SYNTAX	INTEGER
			MAX-ACCESS	read-only
			STATUS	current
			::= { hmWanMbusA0 29 }

hmWanMbusA0VIF0C		OBJECT-TYPE
			SYNTAX	INTEGER
			MAX-ACCESS	read-only
			STATUS	current
			::= { hmWanMbusA0 30 }

hmWanMbusA0Value0C		OBJECT-TYPE
			SYNTAX	INTEGER
			MAX-ACCESS	read-only
			STATUS	current
			::= { hmWanMbusA0 31 }

hmWanMbusA0VIF0D		OBJECT-TYPE
			SYNTAX	INTEGER
			MAX-ACCESS	read-only
			STATUS	current
			::= { hmWanMbusA0 32 }

hmWanMbusA0Value0D		OBJECT-TYPE
			SYNTAX	INTEGER
			MAX-ACCESS	read-only
			STATUS	current
			::= { hmWanMbusA0 33 }

hmWanMbusA0VIF0E		OBJECT-TYPE
			SYNTAX	INTEGER
			MAX-ACCESS	read-only
			STATUS	current
			::= { hmWanMbusA0 34 }

hmWanMbusA0Value0E		OBJECT-TYPE
			SYNTAX	INTEGER
			MAX-ACCESS	read-only
			STATUS	current
			::= { hmWanMbusA0 35 }

hmWanMbusA0VIF0F		OBJECT-TYPE
			SYNTAX	INTEGER
			MAX-ACCESS	read-only
			STATUS	current
			::= { hmWanMbusA0 36 }

hmWanMbusA0Value0F		OBJECT-TYPE
			SYNTAX	INTEGER
			MAX-ACCESS	read-only
			STATUS	current
			::= { hmWanMbusA0 37 }

hmWanMbusA0VIF10		OBJECT-TYPE
			SYNTAX	INTEGER
			MAX-ACCESS	read-only
			STATUS	current
			::= { hmWanMbusA0 38 }

hmWanMbusA0Value10		OBJECT-TYPE
			SYNTAX	INTEGER
			MAX-ACCESS	read-only
			STATUS	current
			::= { hmWanMbusA0 39 }

hmWanMbusA0VIF11		OBJECT-TYPE
			SYNTAX	INTEGER
			MAX-ACCESS	read-only
			STATUS	current
			::= { hmWanMbusA0 40 }

hmWanMbusA0Value11		OBJECT-TYPE
			SYNTAX	INTEGER
			MAX-ACCESS	read-only
			STATUS	current
			::= { hmWanMbusA0 41 }

hmWanMbusA0VIF12		OBJECT-TYPE
			SYNTAX	INTEGER
			MAX-ACCESS	read-only
			STATUS	current
			::= { hmWanMbusA0 42 }

hmWanMbusA0Value12		OBJECT-TYPE
			SYNTAX	INTEGER
			MAX-ACCESS	read-only
			STATUS	current
			::= { hmWanMbusA0 43 }

hmWanMbusA0VIF13		OBJECT-TYPE
			SYNTAX	INTEGER
			MAX-ACCESS	read-only
			STATUS	current
			::= { hmWanMbusA0 44 }

hmWanMbusA0Value13		OBJECT-TYPE
			SYNTAX	INTEGER
			MAX-ACCESS	read-only
			STATUS	current
			::= { hmWanMbusA0 45 }

hmWanMbusA0VIF14		OBJECT-TYPE
			SYNTAX	INTEGER
			MAX-ACCESS	read-only
			STATUS	current
			::= { hmWanMbusA0 46 }

hmWanMbusA0Value14		OBJECT-TYPE
			SYNTAX	INTEGER
			MAX-ACCESS	read-only
			STATUS	current
			::= { hmWanMbusA0 47 }

hmWanMbusA0VIF15		OBJECT-TYPE
			SYNTAX	INTEGER
			MAX-ACCESS	read-only
			STATUS	current
			::= { hmWanMbusA0 48 }

hmWanMbusA0Value15		OBJECT-TYPE
			SYNTAX	INTEGER
			MAX-ACCESS	read-only
			STATUS	current
			::= { hmWanMbusA0 49 }

hmWanMbusA0VIF16		OBJECT-TYPE
			SYNTAX	INTEGER
			MAX-ACCESS	read-only
			STATUS	current
			::= { hmWanMbusA0 50 }

hmWanMbusA0Value16		OBJECT-TYPE
			SYNTAX	INTEGER
			MAX-ACCESS	read-only
			STATUS	current
			::= { hmWanMbusA0 51 }

hmWanMbusA0VIF17		OBJECT-TYPE
			SYNTAX	INTEGER
			MAX-ACCESS	read-only
			STATUS	current
			::= { hmWanMbusA0 52 }

hmWanMbusA0Value17		OBJECT-TYPE
			SYNTAX	INTEGER
			MAX-ACCESS	read-only
			STATUS	current
			::= { hmWanMbusA0 53 }

hmWanMbusA0VIF18		OBJECT-TYPE
			SYNTAX	INTEGER
			MAX-ACCESS	read-only
			STATUS	current
			::= { hmWanMbusA0 54 }

hmWanMbusA0Value18		OBJECT-TYPE
			SYNTAX	INTEGER
			MAX-ACCESS	read-only
			STATUS	current
			::= { hmWanMbusA0 55 }

hmWanMbusA0VIF19		OBJECT-TYPE
			SYNTAX	INTEGER
			MAX-ACCESS	read-only
			STATUS	current
			::= { hmWanMbusA0 56 }

hmWanMbusA0Value19		OBJECT-TYPE
			SYNTAX	INTEGER
			MAX-ACCESS	read-only
			STATUS	current
			::= { hmWanMbusA0 57 }

hmWanMbusA0VIF1A		OBJECT-TYPE
			SYNTAX	INTEGER
			MAX-ACCESS	read-only
			STATUS	current
			::= { hmWanMbusA0 58 }

hmWanMbusA0Value1A		OBJECT-TYPE
			SYNTAX	INTEGER
			MAX-ACCESS	read-only
			STATUS	current
			::= { hmWanMbusA0 59 }

hmWanMbusA0VIF1B		OBJECT-TYPE
			SYNTAX	INTEGER
			MAX-ACCESS	read-only
			STATUS	current
			::= { hmWanMbusA0 60 }

hmWanMbusA0Value1B		OBJECT-TYPE
			SYNTAX	INTEGER
			MAX-ACCESS	read-only
			STATUS	current
			::= { hmWanMbusA0 61 }

hmWanMbusA0VIF1C		OBJECT-TYPE
			SYNTAX	INTEGER
			MAX-ACCESS	read-only
			STATUS	current
			::= { hmWanMbusA0 62 }

hmWanMbusA0Value1C		OBJECT-TYPE
			SYNTAX	INTEGER
			MAX-ACCESS	read-only
			STATUS	current
			::= { hmWanMbusA0 63 }

hmWanMbusA0VIF1D		OBJECT-TYPE
			SYNTAX	INTEGER
			MAX-ACCESS	read-only
			STATUS	current
			::= { hmWanMbusA0 64 }

hmWanMbusA0Value1D		OBJECT-TYPE
			SYNTAX	INTEGER
			MAX-ACCESS	read-only
			STATUS	current
			::= { hmWanMbusA0 65 }

hmWanMbusA0VIF1E		OBJECT-TYPE
			SYNTAX	INTEGER
			MAX-ACCESS	read-only
			STATUS	current
			::= { hmWanMbusA0 66 }

hmWanMbusA0Value1E		OBJECT-TYPE
			SYNTAX	INTEGER
			MAX-ACCESS	read-only
			STATUS	current
			::= { hmWanMbusA0 67 }

hmWanMbusA0VIF1F		OBJECT-TYPE
			SYNTAX	INTEGER
			MAX-ACCESS	read-only
			STATUS	current
			::= { hmWanMbusA0 68 }

hmWanMbusA0Value1F		OBJECT-TYPE
			SYNTAX	INTEGER
			MAX-ACCESS	read-only
			STATUS	current
			::= { hmWanMbusA0 69 }

hmWanMbusA0VIF20		OBJECT-TYPE
			SYNTAX	INTEGER
			MAX-ACCESS	read-only
			STATUS	current
			::= { hmWanMbusA0 70 }

hmWanMbusA0Value20		OBJECT-TYPE
			SYNTAX	INTEGER
			MAX-ACCESS	read-only
			STATUS	current
			::= { hmWanMbusA0 71 }

hmWanMbusA0VIF21		OBJECT-TYPE
			SYNTAX	INTEGER
			MAX-ACCESS	read-only
			STATUS	current
			::= { hmWanMbusA0 72 }

hmWanMbusA0Value21		OBJECT-TYPE
			SYNTAX	INTEGER
			MAX-ACCESS	read-only
			STATUS	current
			::= { hmWanMbusA0 73 }

hmWanMbusA0VIF22		OBJECT-TYPE
			SYNTAX	INTEGER
			MAX-ACCESS	read-only
			STATUS	current
			::= { hmWanMbusA0 74 }

hmWanMbusA0Value22		OBJECT-TYPE
			SYNTAX	INTEGER
			MAX-ACCESS	read-only
			STATUS	current
			::= { hmWanMbusA0 75 }

hmWanMbusA0VIF23		OBJECT-TYPE
			SYNTAX	INTEGER
			MAX-ACCESS	read-only
			STATUS	current
			::= { hmWanMbusA0 76 }

hmWanMbusA0Value23		OBJECT-TYPE
			SYNTAX	INTEGER
			MAX-ACCESS	read-only
			STATUS	current
			::= { hmWanMbusA0 77 }

hmWanMbusA0VIF24		OBJECT-TYPE
			SYNTAX	INTEGER
			MAX-ACCESS	read-only
			STATUS	current
			::= { hmWanMbusA0 78 }

hmWanMbusA0Value24		OBJECT-TYPE
			SYNTAX	INTEGER
			MAX-ACCESS	read-only
			STATUS	current
			::= { hmWanMbusA0 79 }

hmWanMbusA0VIF25		OBJECT-TYPE
			SYNTAX	INTEGER
			MAX-ACCESS	read-only
			STATUS	current
			::= { hmWanMbusA0 80 }

hmWanMbusA0Value25		OBJECT-TYPE
			SYNTAX	INTEGER
			MAX-ACCESS	read-only
			STATUS	current
			::= { hmWanMbusA0 81 }

hmWanMbusA0VIF26		OBJECT-TYPE
			SYNTAX	INTEGER
			MAX-ACCESS	read-only
			STATUS	current
			::= { hmWanMbusA0 82 }

hmWanMbusA0Value26		OBJECT-TYPE
			SYNTAX	INTEGER
			MAX-ACCESS	read-only
			STATUS	current
			::= { hmWanMbusA0 83 }

hmWanMbusA0VIF27		OBJECT-TYPE
			SYNTAX	INTEGER
			MAX-ACCESS	read-only
			STATUS	current
			::= { hmWanMbusA0 84 }

hmWanMbusA0Value27		OBJECT-TYPE
			SYNTAX	INTEGER
			MAX-ACCESS	read-only
			STATUS	current
			::= { hmWanMbusA0 85 }

hmWanMbusA0VIF28		OBJECT-TYPE
			SYNTAX	INTEGER
			MAX-ACCESS	read-only
			STATUS	current
			::= { hmWanMbusA0 86 }

hmWanMbusA0Value28		OBJECT-TYPE
			SYNTAX	INTEGER
			MAX-ACCESS	read-only
			STATUS	current
			::= { hmWanMbusA0 87 }

hmWanMbusA0VIF29		OBJECT-TYPE
			SYNTAX	INTEGER
			MAX-ACCESS	read-only
			STATUS	current
			::= { hmWanMbusA0 88 }

hmWanMbusA0Value29		OBJECT-TYPE
			SYNTAX	INTEGER
			MAX-ACCESS	read-only
			STATUS	current
			::= { hmWanMbusA0 89 }

hmWanMbusA0VIF2A		OBJECT-TYPE
			SYNTAX	INTEGER
			MAX-ACCESS	read-only
			STATUS	current
			::= { hmWanMbusA0 90 }

hmWanMbusA0Value2A		OBJECT-TYPE
			SYNTAX	INTEGER
			MAX-ACCESS	read-only
			STATUS	current
			::= { hmWanMbusA0 91 }

hmWanMbusA0VIF2B		OBJECT-TYPE
			SYNTAX	INTEGER
			MAX-ACCESS	read-only
			STATUS	current
			::= { hmWanMbusA0 92 }

hmWanMbusA0Value2B		OBJECT-TYPE
			SYNTAX	INTEGER
			MAX-ACCESS	read-only
			STATUS	current
			::= { hmWanMbusA0 93 }

hmWanMbusA0VIF2C		OBJECT-TYPE
			SYNTAX	INTEGER
			MAX-ACCESS	read-only
			STATUS	current
			::= { hmWanMbusA0 94 }

hmWanMbusA0Value2C		OBJECT-TYPE
			SYNTAX	INTEGER
			MAX-ACCESS	read-only
			STATUS	current
			::= { hmWanMbusA0 95 }

hmWanMbusA0VIF2D		OBJECT-TYPE
			SYNTAX	INTEGER
			MAX-ACCESS	read-only
			STATUS	current
			::= { hmWanMbusA0 96 }

hmWanMbusA0Value2D		OBJECT-TYPE
			SYNTAX	INTEGER
			MAX-ACCESS	read-only
			STATUS	current
			::= { hmWanMbusA0 97 }

hmWanMbusA0VIF2E		OBJECT-TYPE
			SYNTAX	INTEGER
			MAX-ACCESS	read-only
			STATUS	current
			::= { hmWanMbusA0 98 }

hmWanMbusA0Value2E		OBJECT-TYPE
			SYNTAX	INTEGER
			MAX-ACCESS	read-only
			STATUS	current
			::= { hmWanMbusA0 99 }

hmWanMbusA0VIF2F		OBJECT-TYPE
			SYNTAX	INTEGER
			MAX-ACCESS	read-only
			STATUS	current
			::= { hmWanMbusA0 100 }

hmWanMbusA0Value2F		OBJECT-TYPE
			SYNTAX	INTEGER
			MAX-ACCESS	read-only
			STATUS	current
			::= { hmWanMbusA0 101 }

hmWanMbusA1			OBJECT IDENTIFIER ::= { hmWanMbus 161 }

hmWanMbusA1IdNumber		OBJECT-TYPE
			SYNTAX	Gauge32
			MAX-ACCESS	read-only
			STATUS	current
			::= { hmWanMbusA1 1 }

hmWanMbusA1Manufacturer	OBJECT-TYPE
			SYNTAX	Gauge32
			MAX-ACCESS	read-only
			STATUS	current
			::= { hmWanMbusA1 2 }

hmWanMbusA1Version		OBJECT-TYPE
			SYNTAX	Gauge32
			MAX-ACCESS	read-only
			STATUS	current
			::= { hmWanMbusA1 3 }

hmWanMbusA1Medium		OBJECT-TYPE
			SYNTAX	Gauge32
			MAX-ACCESS	read-only
			STATUS	current
			::= { hmWanMbusA1 4 }

hmWanMbusA1Status		OBJECT-TYPE
			SYNTAX	Gauge32
			MAX-ACCESS	read-only
			STATUS	current
			::= { hmWanMbusA1 5 }

hmWanMbusA1VIF00		OBJECT-TYPE
			SYNTAX	INTEGER
			MAX-ACCESS	read-only
			STATUS	current
			::= { hmWanMbusA1 6 }

hmWanMbusA1Value00		OBJECT-TYPE
			SYNTAX	INTEGER
			MAX-ACCESS	read-only
			STATUS	current
			::= { hmWanMbusA1 7 }

hmWanMbusA1VIF01		OBJECT-TYPE
			SYNTAX	INTEGER
			MAX-ACCESS	read-only
			STATUS	current
			::= { hmWanMbusA1 8 }

hmWanMbusA1Value01		OBJECT-TYPE
			SYNTAX	INTEGER
			MAX-ACCESS	read-only
			STATUS	current
			::= { hmWanMbusA1 9 }

hmWanMbusA1VIF02		OBJECT-TYPE
			SYNTAX	INTEGER
			MAX-ACCESS	read-only
			STATUS	current
			::= { hmWanMbusA1 10 }

hmWanMbusA1Value02		OBJECT-TYPE
			SYNTAX	INTEGER
			MAX-ACCESS	read-only
			STATUS	current
			::= { hmWanMbusA1 11 }

hmWanMbusA1VIF03		OBJECT-TYPE
			SYNTAX	INTEGER
			MAX-ACCESS	read-only
			STATUS	current
			::= { hmWanMbusA1 12 }

hmWanMbusA1Value03		OBJECT-TYPE
			SYNTAX	INTEGER
			MAX-ACCESS	read-only
			STATUS	current
			::= { hmWanMbusA1 13 }

hmWanMbusA1VIF04		OBJECT-TYPE
			SYNTAX	INTEGER
			MAX-ACCESS	read-only
			STATUS	current
			::= { hmWanMbusA1 14 }

hmWanMbusA1Value04		OBJECT-TYPE
			SYNTAX	INTEGER
			MAX-ACCESS	read-only
			STATUS	current
			::= { hmWanMbusA1 15 }

hmWanMbusA1VIF05		OBJECT-TYPE
			SYNTAX	INTEGER
			MAX-ACCESS	read-only
			STATUS	current
			::= { hmWanMbusA1 16 }

hmWanMbusA1Value05		OBJECT-TYPE
			SYNTAX	INTEGER
			MAX-ACCESS	read-only
			STATUS	current
			::= { hmWanMbusA1 17 }

hmWanMbusA1VIF06		OBJECT-TYPE
			SYNTAX	INTEGER
			MAX-ACCESS	read-only
			STATUS	current
			::= { hmWanMbusA1 18 }

hmWanMbusA1Value06		OBJECT-TYPE
			SYNTAX	INTEGER
			MAX-ACCESS	read-only
			STATUS	current
			::= { hmWanMbusA1 19 }

hmWanMbusA1VIF07		OBJECT-TYPE
			SYNTAX	INTEGER
			MAX-ACCESS	read-only
			STATUS	current
			::= { hmWanMbusA1 20 }

hmWanMbusA1Value07		OBJECT-TYPE
			SYNTAX	INTEGER
			MAX-ACCESS	read-only
			STATUS	current
			::= { hmWanMbusA1 21 }

hmWanMbusA1VIF08		OBJECT-TYPE
			SYNTAX	INTEGER
			MAX-ACCESS	read-only
			STATUS	current
			::= { hmWanMbusA1 22 }

hmWanMbusA1Value08		OBJECT-TYPE
			SYNTAX	INTEGER
			MAX-ACCESS	read-only
			STATUS	current
			::= { hmWanMbusA1 23 }

hmWanMbusA1VIF09		OBJECT-TYPE
			SYNTAX	INTEGER
			MAX-ACCESS	read-only
			STATUS	current
			::= { hmWanMbusA1 24 }

hmWanMbusA1Value09		OBJECT-TYPE
			SYNTAX	INTEGER
			MAX-ACCESS	read-only
			STATUS	current
			::= { hmWanMbusA1 25 }

hmWanMbusA1VIF0A		OBJECT-TYPE
			SYNTAX	INTEGER
			MAX-ACCESS	read-only
			STATUS	current
			::= { hmWanMbusA1 26 }

hmWanMbusA1Value0A		OBJECT-TYPE
			SYNTAX	INTEGER
			MAX-ACCESS	read-only
			STATUS	current
			::= { hmWanMbusA1 27 }

hmWanMbusA1VIF0B		OBJECT-TYPE
			SYNTAX	INTEGER
			MAX-ACCESS	read-only
			STATUS	current
			::= { hmWanMbusA1 28 }

hmWanMbusA1Value0B		OBJECT-TYPE
			SYNTAX	INTEGER
			MAX-ACCESS	read-only
			STATUS	current
			::= { hmWanMbusA1 29 }

hmWanMbusA1VIF0C		OBJECT-TYPE
			SYNTAX	INTEGER
			MAX-ACCESS	read-only
			STATUS	current
			::= { hmWanMbusA1 30 }

hmWanMbusA1Value0C		OBJECT-TYPE
			SYNTAX	INTEGER
			MAX-ACCESS	read-only
			STATUS	current
			::= { hmWanMbusA1 31 }

hmWanMbusA1VIF0D		OBJECT-TYPE
			SYNTAX	INTEGER
			MAX-ACCESS	read-only
			STATUS	current
			::= { hmWanMbusA1 32 }

hmWanMbusA1Value0D		OBJECT-TYPE
			SYNTAX	INTEGER
			MAX-ACCESS	read-only
			STATUS	current
			::= { hmWanMbusA1 33 }

hmWanMbusA1VIF0E		OBJECT-TYPE
			SYNTAX	INTEGER
			MAX-ACCESS	read-only
			STATUS	current
			::= { hmWanMbusA1 34 }

hmWanMbusA1Value0E		OBJECT-TYPE
			SYNTAX	INTEGER
			MAX-ACCESS	read-only
			STATUS	current
			::= { hmWanMbusA1 35 }

hmWanMbusA1VIF0F		OBJECT-TYPE
			SYNTAX	INTEGER
			MAX-ACCESS	read-only
			STATUS	current
			::= { hmWanMbusA1 36 }

hmWanMbusA1Value0F		OBJECT-TYPE
			SYNTAX	INTEGER
			MAX-ACCESS	read-only
			STATUS	current
			::= { hmWanMbusA1 37 }

hmWanMbusA1VIF10		OBJECT-TYPE
			SYNTAX	INTEGER
			MAX-ACCESS	read-only
			STATUS	current
			::= { hmWanMbusA1 38 }

hmWanMbusA1Value10		OBJECT-TYPE
			SYNTAX	INTEGER
			MAX-ACCESS	read-only
			STATUS	current
			::= { hmWanMbusA1 39 }

hmWanMbusA1VIF11		OBJECT-TYPE
			SYNTAX	INTEGER
			MAX-ACCESS	read-only
			STATUS	current
			::= { hmWanMbusA1 40 }

hmWanMbusA1Value11		OBJECT-TYPE
			SYNTAX	INTEGER
			MAX-ACCESS	read-only
			STATUS	current
			::= { hmWanMbusA1 41 }

hmWanMbusA1VIF12		OBJECT-TYPE
			SYNTAX	INTEGER
			MAX-ACCESS	read-only
			STATUS	current
			::= { hmWanMbusA1 42 }

hmWanMbusA1Value12		OBJECT-TYPE
			SYNTAX	INTEGER
			MAX-ACCESS	read-only
			STATUS	current
			::= { hmWanMbusA1 43 }

hmWanMbusA1VIF13		OBJECT-TYPE
			SYNTAX	INTEGER
			MAX-ACCESS	read-only
			STATUS	current
			::= { hmWanMbusA1 44 }

hmWanMbusA1Value13		OBJECT-TYPE
			SYNTAX	INTEGER
			MAX-ACCESS	read-only
			STATUS	current
			::= { hmWanMbusA1 45 }

hmWanMbusA1VIF14		OBJECT-TYPE
			SYNTAX	INTEGER
			MAX-ACCESS	read-only
			STATUS	current
			::= { hmWanMbusA1 46 }

hmWanMbusA1Value14		OBJECT-TYPE
			SYNTAX	INTEGER
			MAX-ACCESS	read-only
			STATUS	current
			::= { hmWanMbusA1 47 }

hmWanMbusA1VIF15		OBJECT-TYPE
			SYNTAX	INTEGER
			MAX-ACCESS	read-only
			STATUS	current
			::= { hmWanMbusA1 48 }

hmWanMbusA1Value15		OBJECT-TYPE
			SYNTAX	INTEGER
			MAX-ACCESS	read-only
			STATUS	current
			::= { hmWanMbusA1 49 }

hmWanMbusA1VIF16		OBJECT-TYPE
			SYNTAX	INTEGER
			MAX-ACCESS	read-only
			STATUS	current
			::= { hmWanMbusA1 50 }

hmWanMbusA1Value16		OBJECT-TYPE
			SYNTAX	INTEGER
			MAX-ACCESS	read-only
			STATUS	current
			::= { hmWanMbusA1 51 }

hmWanMbusA1VIF17		OBJECT-TYPE
			SYNTAX	INTEGER
			MAX-ACCESS	read-only
			STATUS	current
			::= { hmWanMbusA1 52 }

hmWanMbusA1Value17		OBJECT-TYPE
			SYNTAX	INTEGER
			MAX-ACCESS	read-only
			STATUS	current
			::= { hmWanMbusA1 53 }

hmWanMbusA1VIF18		OBJECT-TYPE
			SYNTAX	INTEGER
			MAX-ACCESS	read-only
			STATUS	current
			::= { hmWanMbusA1 54 }

hmWanMbusA1Value18		OBJECT-TYPE
			SYNTAX	INTEGER
			MAX-ACCESS	read-only
			STATUS	current
			::= { hmWanMbusA1 55 }

hmWanMbusA1VIF19		OBJECT-TYPE
			SYNTAX	INTEGER
			MAX-ACCESS	read-only
			STATUS	current
			::= { hmWanMbusA1 56 }

hmWanMbusA1Value19		OBJECT-TYPE
			SYNTAX	INTEGER
			MAX-ACCESS	read-only
			STATUS	current
			::= { hmWanMbusA1 57 }

hmWanMbusA1VIF1A		OBJECT-TYPE
			SYNTAX	INTEGER
			MAX-ACCESS	read-only
			STATUS	current
			::= { hmWanMbusA1 58 }

hmWanMbusA1Value1A		OBJECT-TYPE
			SYNTAX	INTEGER
			MAX-ACCESS	read-only
			STATUS	current
			::= { hmWanMbusA1 59 }

hmWanMbusA1VIF1B		OBJECT-TYPE
			SYNTAX	INTEGER
			MAX-ACCESS	read-only
			STATUS	current
			::= { hmWanMbusA1 60 }

hmWanMbusA1Value1B		OBJECT-TYPE
			SYNTAX	INTEGER
			MAX-ACCESS	read-only
			STATUS	current
			::= { hmWanMbusA1 61 }

hmWanMbusA1VIF1C		OBJECT-TYPE
			SYNTAX	INTEGER
			MAX-ACCESS	read-only
			STATUS	current
			::= { hmWanMbusA1 62 }

hmWanMbusA1Value1C		OBJECT-TYPE
			SYNTAX	INTEGER
			MAX-ACCESS	read-only
			STATUS	current
			::= { hmWanMbusA1 63 }

hmWanMbusA1VIF1D		OBJECT-TYPE
			SYNTAX	INTEGER
			MAX-ACCESS	read-only
			STATUS	current
			::= { hmWanMbusA1 64 }

hmWanMbusA1Value1D		OBJECT-TYPE
			SYNTAX	INTEGER
			MAX-ACCESS	read-only
			STATUS	current
			::= { hmWanMbusA1 65 }

hmWanMbusA1VIF1E		OBJECT-TYPE
			SYNTAX	INTEGER
			MAX-ACCESS	read-only
			STATUS	current
			::= { hmWanMbusA1 66 }

hmWanMbusA1Value1E		OBJECT-TYPE
			SYNTAX	INTEGER
			MAX-ACCESS	read-only
			STATUS	current
			::= { hmWanMbusA1 67 }

hmWanMbusA1VIF1F		OBJECT-TYPE
			SYNTAX	INTEGER
			MAX-ACCESS	read-only
			STATUS	current
			::= { hmWanMbusA1 68 }

hmWanMbusA1Value1F		OBJECT-TYPE
			SYNTAX	INTEGER
			MAX-ACCESS	read-only
			STATUS	current
			::= { hmWanMbusA1 69 }

hmWanMbusA1VIF20		OBJECT-TYPE
			SYNTAX	INTEGER
			MAX-ACCESS	read-only
			STATUS	current
			::= { hmWanMbusA1 70 }

hmWanMbusA1Value20		OBJECT-TYPE
			SYNTAX	INTEGER
			MAX-ACCESS	read-only
			STATUS	current
			::= { hmWanMbusA1 71 }

hmWanMbusA1VIF21		OBJECT-TYPE
			SYNTAX	INTEGER
			MAX-ACCESS	read-only
			STATUS	current
			::= { hmWanMbusA1 72 }

hmWanMbusA1Value21		OBJECT-TYPE
			SYNTAX	INTEGER
			MAX-ACCESS	read-only
			STATUS	current
			::= { hmWanMbusA1 73 }

hmWanMbusA1VIF22		OBJECT-TYPE
			SYNTAX	INTEGER
			MAX-ACCESS	read-only
			STATUS	current
			::= { hmWanMbusA1 74 }

hmWanMbusA1Value22		OBJECT-TYPE
			SYNTAX	INTEGER
			MAX-ACCESS	read-only
			STATUS	current
			::= { hmWanMbusA1 75 }

hmWanMbusA1VIF23		OBJECT-TYPE
			SYNTAX	INTEGER
			MAX-ACCESS	read-only
			STATUS	current
			::= { hmWanMbusA1 76 }

hmWanMbusA1Value23		OBJECT-TYPE
			SYNTAX	INTEGER
			MAX-ACCESS	read-only
			STATUS	current
			::= { hmWanMbusA1 77 }

hmWanMbusA1VIF24		OBJECT-TYPE
			SYNTAX	INTEGER
			MAX-ACCESS	read-only
			STATUS	current
			::= { hmWanMbusA1 78 }

hmWanMbusA1Value24		OBJECT-TYPE
			SYNTAX	INTEGER
			MAX-ACCESS	read-only
			STATUS	current
			::= { hmWanMbusA1 79 }

hmWanMbusA1VIF25		OBJECT-TYPE
			SYNTAX	INTEGER
			MAX-ACCESS	read-only
			STATUS	current
			::= { hmWanMbusA1 80 }

hmWanMbusA1Value25		OBJECT-TYPE
			SYNTAX	INTEGER
			MAX-ACCESS	read-only
			STATUS	current
			::= { hmWanMbusA1 81 }

hmWanMbusA1VIF26		OBJECT-TYPE
			SYNTAX	INTEGER
			MAX-ACCESS	read-only
			STATUS	current
			::= { hmWanMbusA1 82 }

hmWanMbusA1Value26		OBJECT-TYPE
			SYNTAX	INTEGER
			MAX-ACCESS	read-only
			STATUS	current
			::= { hmWanMbusA1 83 }

hmWanMbusA1VIF27		OBJECT-TYPE
			SYNTAX	INTEGER
			MAX-ACCESS	read-only
			STATUS	current
			::= { hmWanMbusA1 84 }

hmWanMbusA1Value27		OBJECT-TYPE
			SYNTAX	INTEGER
			MAX-ACCESS	read-only
			STATUS	current
			::= { hmWanMbusA1 85 }

hmWanMbusA1VIF28		OBJECT-TYPE
			SYNTAX	INTEGER
			MAX-ACCESS	read-only
			STATUS	current
			::= { hmWanMbusA1 86 }

hmWanMbusA1Value28		OBJECT-TYPE
			SYNTAX	INTEGER
			MAX-ACCESS	read-only
			STATUS	current
			::= { hmWanMbusA1 87 }

hmWanMbusA1VIF29		OBJECT-TYPE
			SYNTAX	INTEGER
			MAX-ACCESS	read-only
			STATUS	current
			::= { hmWanMbusA1 88 }

hmWanMbusA1Value29		OBJECT-TYPE
			SYNTAX	INTEGER
			MAX-ACCESS	read-only
			STATUS	current
			::= { hmWanMbusA1 89 }

hmWanMbusA1VIF2A		OBJECT-TYPE
			SYNTAX	INTEGER
			MAX-ACCESS	read-only
			STATUS	current
			::= { hmWanMbusA1 90 }

hmWanMbusA1Value2A		OBJECT-TYPE
			SYNTAX	INTEGER
			MAX-ACCESS	read-only
			STATUS	current
			::= { hmWanMbusA1 91 }

hmWanMbusA1VIF2B		OBJECT-TYPE
			SYNTAX	INTEGER
			MAX-ACCESS	read-only
			STATUS	current
			::= { hmWanMbusA1 92 }

hmWanMbusA1Value2B		OBJECT-TYPE
			SYNTAX	INTEGER
			MAX-ACCESS	read-only
			STATUS	current
			::= { hmWanMbusA1 93 }

hmWanMbusA1VIF2C		OBJECT-TYPE
			SYNTAX	INTEGER
			MAX-ACCESS	read-only
			STATUS	current
			::= { hmWanMbusA1 94 }

hmWanMbusA1Value2C		OBJECT-TYPE
			SYNTAX	INTEGER
			MAX-ACCESS	read-only
			STATUS	current
			::= { hmWanMbusA1 95 }

hmWanMbusA1VIF2D		OBJECT-TYPE
			SYNTAX	INTEGER
			MAX-ACCESS	read-only
			STATUS	current
			::= { hmWanMbusA1 96 }

hmWanMbusA1Value2D		OBJECT-TYPE
			SYNTAX	INTEGER
			MAX-ACCESS	read-only
			STATUS	current
			::= { hmWanMbusA1 97 }

hmWanMbusA1VIF2E		OBJECT-TYPE
			SYNTAX	INTEGER
			MAX-ACCESS	read-only
			STATUS	current
			::= { hmWanMbusA1 98 }

hmWanMbusA1Value2E		OBJECT-TYPE
			SYNTAX	INTEGER
			MAX-ACCESS	read-only
			STATUS	current
			::= { hmWanMbusA1 99 }

hmWanMbusA1VIF2F		OBJECT-TYPE
			SYNTAX	INTEGER
			MAX-ACCESS	read-only
			STATUS	current
			::= { hmWanMbusA1 100 }

hmWanMbusA1Value2F		OBJECT-TYPE
			SYNTAX	INTEGER
			MAX-ACCESS	read-only
			STATUS	current
			::= { hmWanMbusA1 101 }

hmWanMbusA2			OBJECT IDENTIFIER ::= { hmWanMbus 162 }

hmWanMbusA2IdNumber		OBJECT-TYPE
			SYNTAX	Gauge32
			MAX-ACCESS	read-only
			STATUS	current
			::= { hmWanMbusA2 1 }

hmWanMbusA2Manufacturer	OBJECT-TYPE
			SYNTAX	Gauge32
			MAX-ACCESS	read-only
			STATUS	current
			::= { hmWanMbusA2 2 }

hmWanMbusA2Version		OBJECT-TYPE
			SYNTAX	Gauge32
			MAX-ACCESS	read-only
			STATUS	current
			::= { hmWanMbusA2 3 }

hmWanMbusA2Medium		OBJECT-TYPE
			SYNTAX	Gauge32
			MAX-ACCESS	read-only
			STATUS	current
			::= { hmWanMbusA2 4 }

hmWanMbusA2Status		OBJECT-TYPE
			SYNTAX	Gauge32
			MAX-ACCESS	read-only
			STATUS	current
			::= { hmWanMbusA2 5 }

hmWanMbusA2VIF00		OBJECT-TYPE
			SYNTAX	INTEGER
			MAX-ACCESS	read-only
			STATUS	current
			::= { hmWanMbusA2 6 }

hmWanMbusA2Value00		OBJECT-TYPE
			SYNTAX	INTEGER
			MAX-ACCESS	read-only
			STATUS	current
			::= { hmWanMbusA2 7 }

hmWanMbusA2VIF01		OBJECT-TYPE
			SYNTAX	INTEGER
			MAX-ACCESS	read-only
			STATUS	current
			::= { hmWanMbusA2 8 }

hmWanMbusA2Value01		OBJECT-TYPE
			SYNTAX	INTEGER
			MAX-ACCESS	read-only
			STATUS	current
			::= { hmWanMbusA2 9 }

hmWanMbusA2VIF02		OBJECT-TYPE
			SYNTAX	INTEGER
			MAX-ACCESS	read-only
			STATUS	current
			::= { hmWanMbusA2 10 }

hmWanMbusA2Value02		OBJECT-TYPE
			SYNTAX	INTEGER
			MAX-ACCESS	read-only
			STATUS	current
			::= { hmWanMbusA2 11 }

hmWanMbusA2VIF03		OBJECT-TYPE
			SYNTAX	INTEGER
			MAX-ACCESS	read-only
			STATUS	current
			::= { hmWanMbusA2 12 }

hmWanMbusA2Value03		OBJECT-TYPE
			SYNTAX	INTEGER
			MAX-ACCESS	read-only
			STATUS	current
			::= { hmWanMbusA2 13 }

hmWanMbusA2VIF04		OBJECT-TYPE
			SYNTAX	INTEGER
			MAX-ACCESS	read-only
			STATUS	current
			::= { hmWanMbusA2 14 }

hmWanMbusA2Value04		OBJECT-TYPE
			SYNTAX	INTEGER
			MAX-ACCESS	read-only
			STATUS	current
			::= { hmWanMbusA2 15 }

hmWanMbusA2VIF05		OBJECT-TYPE
			SYNTAX	INTEGER
			MAX-ACCESS	read-only
			STATUS	current
			::= { hmWanMbusA2 16 }

hmWanMbusA2Value05		OBJECT-TYPE
			SYNTAX	INTEGER
			MAX-ACCESS	read-only
			STATUS	current
			::= { hmWanMbusA2 17 }

hmWanMbusA2VIF06		OBJECT-TYPE
			SYNTAX	INTEGER
			MAX-ACCESS	read-only
			STATUS	current
			::= { hmWanMbusA2 18 }

hmWanMbusA2Value06		OBJECT-TYPE
			SYNTAX	INTEGER
			MAX-ACCESS	read-only
			STATUS	current
			::= { hmWanMbusA2 19 }

hmWanMbusA2VIF07		OBJECT-TYPE
			SYNTAX	INTEGER
			MAX-ACCESS	read-only
			STATUS	current
			::= { hmWanMbusA2 20 }

hmWanMbusA2Value07		OBJECT-TYPE
			SYNTAX	INTEGER
			MAX-ACCESS	read-only
			STATUS	current
			::= { hmWanMbusA2 21 }

hmWanMbusA2VIF08		OBJECT-TYPE
			SYNTAX	INTEGER
			MAX-ACCESS	read-only
			STATUS	current
			::= { hmWanMbusA2 22 }

hmWanMbusA2Value08		OBJECT-TYPE
			SYNTAX	INTEGER
			MAX-ACCESS	read-only
			STATUS	current
			::= { hmWanMbusA2 23 }

hmWanMbusA2VIF09		OBJECT-TYPE
			SYNTAX	INTEGER
			MAX-ACCESS	read-only
			STATUS	current
			::= { hmWanMbusA2 24 }

hmWanMbusA2Value09		OBJECT-TYPE
			SYNTAX	INTEGER
			MAX-ACCESS	read-only
			STATUS	current
			::= { hmWanMbusA2 25 }

hmWanMbusA2VIF0A		OBJECT-TYPE
			SYNTAX	INTEGER
			MAX-ACCESS	read-only
			STATUS	current
			::= { hmWanMbusA2 26 }

hmWanMbusA2Value0A		OBJECT-TYPE
			SYNTAX	INTEGER
			MAX-ACCESS	read-only
			STATUS	current
			::= { hmWanMbusA2 27 }

hmWanMbusA2VIF0B		OBJECT-TYPE
			SYNTAX	INTEGER
			MAX-ACCESS	read-only
			STATUS	current
			::= { hmWanMbusA2 28 }

hmWanMbusA2Value0B		OBJECT-TYPE
			SYNTAX	INTEGER
			MAX-ACCESS	read-only
			STATUS	current
			::= { hmWanMbusA2 29 }

hmWanMbusA2VIF0C		OBJECT-TYPE
			SYNTAX	INTEGER
			MAX-ACCESS	read-only
			STATUS	current
			::= { hmWanMbusA2 30 }

hmWanMbusA2Value0C		OBJECT-TYPE
			SYNTAX	INTEGER
			MAX-ACCESS	read-only
			STATUS	current
			::= { hmWanMbusA2 31 }

hmWanMbusA2VIF0D		OBJECT-TYPE
			SYNTAX	INTEGER
			MAX-ACCESS	read-only
			STATUS	current
			::= { hmWanMbusA2 32 }

hmWanMbusA2Value0D		OBJECT-TYPE
			SYNTAX	INTEGER
			MAX-ACCESS	read-only
			STATUS	current
			::= { hmWanMbusA2 33 }

hmWanMbusA2VIF0E		OBJECT-TYPE
			SYNTAX	INTEGER
			MAX-ACCESS	read-only
			STATUS	current
			::= { hmWanMbusA2 34 }

hmWanMbusA2Value0E		OBJECT-TYPE
			SYNTAX	INTEGER
			MAX-ACCESS	read-only
			STATUS	current
			::= { hmWanMbusA2 35 }

hmWanMbusA2VIF0F		OBJECT-TYPE
			SYNTAX	INTEGER
			MAX-ACCESS	read-only
			STATUS	current
			::= { hmWanMbusA2 36 }

hmWanMbusA2Value0F		OBJECT-TYPE
			SYNTAX	INTEGER
			MAX-ACCESS	read-only
			STATUS	current
			::= { hmWanMbusA2 37 }

hmWanMbusA2VIF10		OBJECT-TYPE
			SYNTAX	INTEGER
			MAX-ACCESS	read-only
			STATUS	current
			::= { hmWanMbusA2 38 }

hmWanMbusA2Value10		OBJECT-TYPE
			SYNTAX	INTEGER
			MAX-ACCESS	read-only
			STATUS	current
			::= { hmWanMbusA2 39 }

hmWanMbusA2VIF11		OBJECT-TYPE
			SYNTAX	INTEGER
			MAX-ACCESS	read-only
			STATUS	current
			::= { hmWanMbusA2 40 }

hmWanMbusA2Value11		OBJECT-TYPE
			SYNTAX	INTEGER
			MAX-ACCESS	read-only
			STATUS	current
			::= { hmWanMbusA2 41 }

hmWanMbusA2VIF12		OBJECT-TYPE
			SYNTAX	INTEGER
			MAX-ACCESS	read-only
			STATUS	current
			::= { hmWanMbusA2 42 }

hmWanMbusA2Value12		OBJECT-TYPE
			SYNTAX	INTEGER
			MAX-ACCESS	read-only
			STATUS	current
			::= { hmWanMbusA2 43 }

hmWanMbusA2VIF13		OBJECT-TYPE
			SYNTAX	INTEGER
			MAX-ACCESS	read-only
			STATUS	current
			::= { hmWanMbusA2 44 }

hmWanMbusA2Value13		OBJECT-TYPE
			SYNTAX	INTEGER
			MAX-ACCESS	read-only
			STATUS	current
			::= { hmWanMbusA2 45 }

hmWanMbusA2VIF14		OBJECT-TYPE
			SYNTAX	INTEGER
			MAX-ACCESS	read-only
			STATUS	current
			::= { hmWanMbusA2 46 }

hmWanMbusA2Value14		OBJECT-TYPE
			SYNTAX	INTEGER
			MAX-ACCESS	read-only
			STATUS	current
			::= { hmWanMbusA2 47 }

hmWanMbusA2VIF15		OBJECT-TYPE
			SYNTAX	INTEGER
			MAX-ACCESS	read-only
			STATUS	current
			::= { hmWanMbusA2 48 }

hmWanMbusA2Value15		OBJECT-TYPE
			SYNTAX	INTEGER
			MAX-ACCESS	read-only
			STATUS	current
			::= { hmWanMbusA2 49 }

hmWanMbusA2VIF16		OBJECT-TYPE
			SYNTAX	INTEGER
			MAX-ACCESS	read-only
			STATUS	current
			::= { hmWanMbusA2 50 }

hmWanMbusA2Value16		OBJECT-TYPE
			SYNTAX	INTEGER
			MAX-ACCESS	read-only
			STATUS	current
			::= { hmWanMbusA2 51 }

hmWanMbusA2VIF17		OBJECT-TYPE
			SYNTAX	INTEGER
			MAX-ACCESS	read-only
			STATUS	current
			::= { hmWanMbusA2 52 }

hmWanMbusA2Value17		OBJECT-TYPE
			SYNTAX	INTEGER
			MAX-ACCESS	read-only
			STATUS	current
			::= { hmWanMbusA2 53 }

hmWanMbusA2VIF18		OBJECT-TYPE
			SYNTAX	INTEGER
			MAX-ACCESS	read-only
			STATUS	current
			::= { hmWanMbusA2 54 }

hmWanMbusA2Value18		OBJECT-TYPE
			SYNTAX	INTEGER
			MAX-ACCESS	read-only
			STATUS	current
			::= { hmWanMbusA2 55 }

hmWanMbusA2VIF19		OBJECT-TYPE
			SYNTAX	INTEGER
			MAX-ACCESS	read-only
			STATUS	current
			::= { hmWanMbusA2 56 }

hmWanMbusA2Value19		OBJECT-TYPE
			SYNTAX	INTEGER
			MAX-ACCESS	read-only
			STATUS	current
			::= { hmWanMbusA2 57 }

hmWanMbusA2VIF1A		OBJECT-TYPE
			SYNTAX	INTEGER
			MAX-ACCESS	read-only
			STATUS	current
			::= { hmWanMbusA2 58 }

hmWanMbusA2Value1A		OBJECT-TYPE
			SYNTAX	INTEGER
			MAX-ACCESS	read-only
			STATUS	current
			::= { hmWanMbusA2 59 }

hmWanMbusA2VIF1B		OBJECT-TYPE
			SYNTAX	INTEGER
			MAX-ACCESS	read-only
			STATUS	current
			::= { hmWanMbusA2 60 }

hmWanMbusA2Value1B		OBJECT-TYPE
			SYNTAX	INTEGER
			MAX-ACCESS	read-only
			STATUS	current
			::= { hmWanMbusA2 61 }

hmWanMbusA2VIF1C		OBJECT-TYPE
			SYNTAX	INTEGER
			MAX-ACCESS	read-only
			STATUS	current
			::= { hmWanMbusA2 62 }

hmWanMbusA2Value1C		OBJECT-TYPE
			SYNTAX	INTEGER
			MAX-ACCESS	read-only
			STATUS	current
			::= { hmWanMbusA2 63 }

hmWanMbusA2VIF1D		OBJECT-TYPE
			SYNTAX	INTEGER
			MAX-ACCESS	read-only
			STATUS	current
			::= { hmWanMbusA2 64 }

hmWanMbusA2Value1D		OBJECT-TYPE
			SYNTAX	INTEGER
			MAX-ACCESS	read-only
			STATUS	current
			::= { hmWanMbusA2 65 }

hmWanMbusA2VIF1E		OBJECT-TYPE
			SYNTAX	INTEGER
			MAX-ACCESS	read-only
			STATUS	current
			::= { hmWanMbusA2 66 }

hmWanMbusA2Value1E		OBJECT-TYPE
			SYNTAX	INTEGER
			MAX-ACCESS	read-only
			STATUS	current
			::= { hmWanMbusA2 67 }

hmWanMbusA2VIF1F		OBJECT-TYPE
			SYNTAX	INTEGER
			MAX-ACCESS	read-only
			STATUS	current
			::= { hmWanMbusA2 68 }

hmWanMbusA2Value1F		OBJECT-TYPE
			SYNTAX	INTEGER
			MAX-ACCESS	read-only
			STATUS	current
			::= { hmWanMbusA2 69 }

hmWanMbusA2VIF20		OBJECT-TYPE
			SYNTAX	INTEGER
			MAX-ACCESS	read-only
			STATUS	current
			::= { hmWanMbusA2 70 }

hmWanMbusA2Value20		OBJECT-TYPE
			SYNTAX	INTEGER
			MAX-ACCESS	read-only
			STATUS	current
			::= { hmWanMbusA2 71 }

hmWanMbusA2VIF21		OBJECT-TYPE
			SYNTAX	INTEGER
			MAX-ACCESS	read-only
			STATUS	current
			::= { hmWanMbusA2 72 }

hmWanMbusA2Value21		OBJECT-TYPE
			SYNTAX	INTEGER
			MAX-ACCESS	read-only
			STATUS	current
			::= { hmWanMbusA2 73 }

hmWanMbusA2VIF22		OBJECT-TYPE
			SYNTAX	INTEGER
			MAX-ACCESS	read-only
			STATUS	current
			::= { hmWanMbusA2 74 }

hmWanMbusA2Value22		OBJECT-TYPE
			SYNTAX	INTEGER
			MAX-ACCESS	read-only
			STATUS	current
			::= { hmWanMbusA2 75 }

hmWanMbusA2VIF23		OBJECT-TYPE
			SYNTAX	INTEGER
			MAX-ACCESS	read-only
			STATUS	current
			::= { hmWanMbusA2 76 }

hmWanMbusA2Value23		OBJECT-TYPE
			SYNTAX	INTEGER
			MAX-ACCESS	read-only
			STATUS	current
			::= { hmWanMbusA2 77 }

hmWanMbusA2VIF24		OBJECT-TYPE
			SYNTAX	INTEGER
			MAX-ACCESS	read-only
			STATUS	current
			::= { hmWanMbusA2 78 }

hmWanMbusA2Value24		OBJECT-TYPE
			SYNTAX	INTEGER
			MAX-ACCESS	read-only
			STATUS	current
			::= { hmWanMbusA2 79 }

hmWanMbusA2VIF25		OBJECT-TYPE
			SYNTAX	INTEGER
			MAX-ACCESS	read-only
			STATUS	current
			::= { hmWanMbusA2 80 }

hmWanMbusA2Value25		OBJECT-TYPE
			SYNTAX	INTEGER
			MAX-ACCESS	read-only
			STATUS	current
			::= { hmWanMbusA2 81 }

hmWanMbusA2VIF26		OBJECT-TYPE
			SYNTAX	INTEGER
			MAX-ACCESS	read-only
			STATUS	current
			::= { hmWanMbusA2 82 }

hmWanMbusA2Value26		OBJECT-TYPE
			SYNTAX	INTEGER
			MAX-ACCESS	read-only
			STATUS	current
			::= { hmWanMbusA2 83 }

hmWanMbusA2VIF27		OBJECT-TYPE
			SYNTAX	INTEGER
			MAX-ACCESS	read-only
			STATUS	current
			::= { hmWanMbusA2 84 }

hmWanMbusA2Value27		OBJECT-TYPE
			SYNTAX	INTEGER
			MAX-ACCESS	read-only
			STATUS	current
			::= { hmWanMbusA2 85 }

hmWanMbusA2VIF28		OBJECT-TYPE
			SYNTAX	INTEGER
			MAX-ACCESS	read-only
			STATUS	current
			::= { hmWanMbusA2 86 }

hmWanMbusA2Value28		OBJECT-TYPE
			SYNTAX	INTEGER
			MAX-ACCESS	read-only
			STATUS	current
			::= { hmWanMbusA2 87 }

hmWanMbusA2VIF29		OBJECT-TYPE
			SYNTAX	INTEGER
			MAX-ACCESS	read-only
			STATUS	current
			::= { hmWanMbusA2 88 }

hmWanMbusA2Value29		OBJECT-TYPE
			SYNTAX	INTEGER
			MAX-ACCESS	read-only
			STATUS	current
			::= { hmWanMbusA2 89 }

hmWanMbusA2VIF2A		OBJECT-TYPE
			SYNTAX	INTEGER
			MAX-ACCESS	read-only
			STATUS	current
			::= { hmWanMbusA2 90 }

hmWanMbusA2Value2A		OBJECT-TYPE
			SYNTAX	INTEGER
			MAX-ACCESS	read-only
			STATUS	current
			::= { hmWanMbusA2 91 }

hmWanMbusA2VIF2B		OBJECT-TYPE
			SYNTAX	INTEGER
			MAX-ACCESS	read-only
			STATUS	current
			::= { hmWanMbusA2 92 }

hmWanMbusA2Value2B		OBJECT-TYPE
			SYNTAX	INTEGER
			MAX-ACCESS	read-only
			STATUS	current
			::= { hmWanMbusA2 93 }

hmWanMbusA2VIF2C		OBJECT-TYPE
			SYNTAX	INTEGER
			MAX-ACCESS	read-only
			STATUS	current
			::= { hmWanMbusA2 94 }

hmWanMbusA2Value2C		OBJECT-TYPE
			SYNTAX	INTEGER
			MAX-ACCESS	read-only
			STATUS	current
			::= { hmWanMbusA2 95 }

hmWanMbusA2VIF2D		OBJECT-TYPE
			SYNTAX	INTEGER
			MAX-ACCESS	read-only
			STATUS	current
			::= { hmWanMbusA2 96 }

hmWanMbusA2Value2D		OBJECT-TYPE
			SYNTAX	INTEGER
			MAX-ACCESS	read-only
			STATUS	current
			::= { hmWanMbusA2 97 }

hmWanMbusA2VIF2E		OBJECT-TYPE
			SYNTAX	INTEGER
			MAX-ACCESS	read-only
			STATUS	current
			::= { hmWanMbusA2 98 }

hmWanMbusA2Value2E		OBJECT-TYPE
			SYNTAX	INTEGER
			MAX-ACCESS	read-only
			STATUS	current
			::= { hmWanMbusA2 99 }

hmWanMbusA2VIF2F		OBJECT-TYPE
			SYNTAX	INTEGER
			MAX-ACCESS	read-only
			STATUS	current
			::= { hmWanMbusA2 100 }

hmWanMbusA2Value2F		OBJECT-TYPE
			SYNTAX	INTEGER
			MAX-ACCESS	read-only
			STATUS	current
			::= { hmWanMbusA2 101 }

hmWanMbusA3			OBJECT IDENTIFIER ::= { hmWanMbus 163 }

hmWanMbusA3IdNumber		OBJECT-TYPE
			SYNTAX	Gauge32
			MAX-ACCESS	read-only
			STATUS	current
			::= { hmWanMbusA3 1 }

hmWanMbusA3Manufacturer	OBJECT-TYPE
			SYNTAX	Gauge32
			MAX-ACCESS	read-only
			STATUS	current
			::= { hmWanMbusA3 2 }

hmWanMbusA3Version		OBJECT-TYPE
			SYNTAX	Gauge32
			MAX-ACCESS	read-only
			STATUS	current
			::= { hmWanMbusA3 3 }

hmWanMbusA3Medium		OBJECT-TYPE
			SYNTAX	Gauge32
			MAX-ACCESS	read-only
			STATUS	current
			::= { hmWanMbusA3 4 }

hmWanMbusA3Status		OBJECT-TYPE
			SYNTAX	Gauge32
			MAX-ACCESS	read-only
			STATUS	current
			::= { hmWanMbusA3 5 }

hmWanMbusA3VIF00		OBJECT-TYPE
			SYNTAX	INTEGER
			MAX-ACCESS	read-only
			STATUS	current
			::= { hmWanMbusA3 6 }

hmWanMbusA3Value00		OBJECT-TYPE
			SYNTAX	INTEGER
			MAX-ACCESS	read-only
			STATUS	current
			::= { hmWanMbusA3 7 }

hmWanMbusA3VIF01		OBJECT-TYPE
			SYNTAX	INTEGER
			MAX-ACCESS	read-only
			STATUS	current
			::= { hmWanMbusA3 8 }

hmWanMbusA3Value01		OBJECT-TYPE
			SYNTAX	INTEGER
			MAX-ACCESS	read-only
			STATUS	current
			::= { hmWanMbusA3 9 }

hmWanMbusA3VIF02		OBJECT-TYPE
			SYNTAX	INTEGER
			MAX-ACCESS	read-only
			STATUS	current
			::= { hmWanMbusA3 10 }

hmWanMbusA3Value02		OBJECT-TYPE
			SYNTAX	INTEGER
			MAX-ACCESS	read-only
			STATUS	current
			::= { hmWanMbusA3 11 }

hmWanMbusA3VIF03		OBJECT-TYPE
			SYNTAX	INTEGER
			MAX-ACCESS	read-only
			STATUS	current
			::= { hmWanMbusA3 12 }

hmWanMbusA3Value03		OBJECT-TYPE
			SYNTAX	INTEGER
			MAX-ACCESS	read-only
			STATUS	current
			::= { hmWanMbusA3 13 }

hmWanMbusA3VIF04		OBJECT-TYPE
			SYNTAX	INTEGER
			MAX-ACCESS	read-only
			STATUS	current
			::= { hmWanMbusA3 14 }

hmWanMbusA3Value04		OBJECT-TYPE
			SYNTAX	INTEGER
			MAX-ACCESS	read-only
			STATUS	current
			::= { hmWanMbusA3 15 }

hmWanMbusA3VIF05		OBJECT-TYPE
			SYNTAX	INTEGER
			MAX-ACCESS	read-only
			STATUS	current
			::= { hmWanMbusA3 16 }

hmWanMbusA3Value05		OBJECT-TYPE
			SYNTAX	INTEGER
			MAX-ACCESS	read-only
			STATUS	current
			::= { hmWanMbusA3 17 }

hmWanMbusA3VIF06		OBJECT-TYPE
			SYNTAX	INTEGER
			MAX-ACCESS	read-only
			STATUS	current
			::= { hmWanMbusA3 18 }

hmWanMbusA3Value06		OBJECT-TYPE
			SYNTAX	INTEGER
			MAX-ACCESS	read-only
			STATUS	current
			::= { hmWanMbusA3 19 }

hmWanMbusA3VIF07		OBJECT-TYPE
			SYNTAX	INTEGER
			MAX-ACCESS	read-only
			STATUS	current
			::= { hmWanMbusA3 20 }

hmWanMbusA3Value07		OBJECT-TYPE
			SYNTAX	INTEGER
			MAX-ACCESS	read-only
			STATUS	current
			::= { hmWanMbusA3 21 }

hmWanMbusA3VIF08		OBJECT-TYPE
			SYNTAX	INTEGER
			MAX-ACCESS	read-only
			STATUS	current
			::= { hmWanMbusA3 22 }

hmWanMbusA3Value08		OBJECT-TYPE
			SYNTAX	INTEGER
			MAX-ACCESS	read-only
			STATUS	current
			::= { hmWanMbusA3 23 }

hmWanMbusA3VIF09		OBJECT-TYPE
			SYNTAX	INTEGER
			MAX-ACCESS	read-only
			STATUS	current
			::= { hmWanMbusA3 24 }

hmWanMbusA3Value09		OBJECT-TYPE
			SYNTAX	INTEGER
			MAX-ACCESS	read-only
			STATUS	current
			::= { hmWanMbusA3 25 }

hmWanMbusA3VIF0A		OBJECT-TYPE
			SYNTAX	INTEGER
			MAX-ACCESS	read-only
			STATUS	current
			::= { hmWanMbusA3 26 }

hmWanMbusA3Value0A		OBJECT-TYPE
			SYNTAX	INTEGER
			MAX-ACCESS	read-only
			STATUS	current
			::= { hmWanMbusA3 27 }

hmWanMbusA3VIF0B		OBJECT-TYPE
			SYNTAX	INTEGER
			MAX-ACCESS	read-only
			STATUS	current
			::= { hmWanMbusA3 28 }

hmWanMbusA3Value0B		OBJECT-TYPE
			SYNTAX	INTEGER
			MAX-ACCESS	read-only
			STATUS	current
			::= { hmWanMbusA3 29 }

hmWanMbusA3VIF0C		OBJECT-TYPE
			SYNTAX	INTEGER
			MAX-ACCESS	read-only
			STATUS	current
			::= { hmWanMbusA3 30 }

hmWanMbusA3Value0C		OBJECT-TYPE
			SYNTAX	INTEGER
			MAX-ACCESS	read-only
			STATUS	current
			::= { hmWanMbusA3 31 }

hmWanMbusA3VIF0D		OBJECT-TYPE
			SYNTAX	INTEGER
			MAX-ACCESS	read-only
			STATUS	current
			::= { hmWanMbusA3 32 }

hmWanMbusA3Value0D		OBJECT-TYPE
			SYNTAX	INTEGER
			MAX-ACCESS	read-only
			STATUS	current
			::= { hmWanMbusA3 33 }

hmWanMbusA3VIF0E		OBJECT-TYPE
			SYNTAX	INTEGER
			MAX-ACCESS	read-only
			STATUS	current
			::= { hmWanMbusA3 34 }

hmWanMbusA3Value0E		OBJECT-TYPE
			SYNTAX	INTEGER
			MAX-ACCESS	read-only
			STATUS	current
			::= { hmWanMbusA3 35 }

hmWanMbusA3VIF0F		OBJECT-TYPE
			SYNTAX	INTEGER
			MAX-ACCESS	read-only
			STATUS	current
			::= { hmWanMbusA3 36 }

hmWanMbusA3Value0F		OBJECT-TYPE
			SYNTAX	INTEGER
			MAX-ACCESS	read-only
			STATUS	current
			::= { hmWanMbusA3 37 }

hmWanMbusA3VIF10		OBJECT-TYPE
			SYNTAX	INTEGER
			MAX-ACCESS	read-only
			STATUS	current
			::= { hmWanMbusA3 38 }

hmWanMbusA3Value10		OBJECT-TYPE
			SYNTAX	INTEGER
			MAX-ACCESS	read-only
			STATUS	current
			::= { hmWanMbusA3 39 }

hmWanMbusA3VIF11		OBJECT-TYPE
			SYNTAX	INTEGER
			MAX-ACCESS	read-only
			STATUS	current
			::= { hmWanMbusA3 40 }

hmWanMbusA3Value11		OBJECT-TYPE
			SYNTAX	INTEGER
			MAX-ACCESS	read-only
			STATUS	current
			::= { hmWanMbusA3 41 }

hmWanMbusA3VIF12		OBJECT-TYPE
			SYNTAX	INTEGER
			MAX-ACCESS	read-only
			STATUS	current
			::= { hmWanMbusA3 42 }

hmWanMbusA3Value12		OBJECT-TYPE
			SYNTAX	INTEGER
			MAX-ACCESS	read-only
			STATUS	current
			::= { hmWanMbusA3 43 }

hmWanMbusA3VIF13		OBJECT-TYPE
			SYNTAX	INTEGER
			MAX-ACCESS	read-only
			STATUS	current
			::= { hmWanMbusA3 44 }

hmWanMbusA3Value13		OBJECT-TYPE
			SYNTAX	INTEGER
			MAX-ACCESS	read-only
			STATUS	current
			::= { hmWanMbusA3 45 }

hmWanMbusA3VIF14		OBJECT-TYPE
			SYNTAX	INTEGER
			MAX-ACCESS	read-only
			STATUS	current
			::= { hmWanMbusA3 46 }

hmWanMbusA3Value14		OBJECT-TYPE
			SYNTAX	INTEGER
			MAX-ACCESS	read-only
			STATUS	current
			::= { hmWanMbusA3 47 }

hmWanMbusA3VIF15		OBJECT-TYPE
			SYNTAX	INTEGER
			MAX-ACCESS	read-only
			STATUS	current
			::= { hmWanMbusA3 48 }

hmWanMbusA3Value15		OBJECT-TYPE
			SYNTAX	INTEGER
			MAX-ACCESS	read-only
			STATUS	current
			::= { hmWanMbusA3 49 }

hmWanMbusA3VIF16		OBJECT-TYPE
			SYNTAX	INTEGER
			MAX-ACCESS	read-only
			STATUS	current
			::= { hmWanMbusA3 50 }

hmWanMbusA3Value16		OBJECT-TYPE
			SYNTAX	INTEGER
			MAX-ACCESS	read-only
			STATUS	current
			::= { hmWanMbusA3 51 }

hmWanMbusA3VIF17		OBJECT-TYPE
			SYNTAX	INTEGER
			MAX-ACCESS	read-only
			STATUS	current
			::= { hmWanMbusA3 52 }

hmWanMbusA3Value17		OBJECT-TYPE
			SYNTAX	INTEGER
			MAX-ACCESS	read-only
			STATUS	current
			::= { hmWanMbusA3 53 }

hmWanMbusA3VIF18		OBJECT-TYPE
			SYNTAX	INTEGER
			MAX-ACCESS	read-only
			STATUS	current
			::= { hmWanMbusA3 54 }

hmWanMbusA3Value18		OBJECT-TYPE
			SYNTAX	INTEGER
			MAX-ACCESS	read-only
			STATUS	current
			::= { hmWanMbusA3 55 }

hmWanMbusA3VIF19		OBJECT-TYPE
			SYNTAX	INTEGER
			MAX-ACCESS	read-only
			STATUS	current
			::= { hmWanMbusA3 56 }

hmWanMbusA3Value19		OBJECT-TYPE
			SYNTAX	INTEGER
			MAX-ACCESS	read-only
			STATUS	current
			::= { hmWanMbusA3 57 }

hmWanMbusA3VIF1A		OBJECT-TYPE
			SYNTAX	INTEGER
			MAX-ACCESS	read-only
			STATUS	current
			::= { hmWanMbusA3 58 }

hmWanMbusA3Value1A		OBJECT-TYPE
			SYNTAX	INTEGER
			MAX-ACCESS	read-only
			STATUS	current
			::= { hmWanMbusA3 59 }

hmWanMbusA3VIF1B		OBJECT-TYPE
			SYNTAX	INTEGER
			MAX-ACCESS	read-only
			STATUS	current
			::= { hmWanMbusA3 60 }

hmWanMbusA3Value1B		OBJECT-TYPE
			SYNTAX	INTEGER
			MAX-ACCESS	read-only
			STATUS	current
			::= { hmWanMbusA3 61 }

hmWanMbusA3VIF1C		OBJECT-TYPE
			SYNTAX	INTEGER
			MAX-ACCESS	read-only
			STATUS	current
			::= { hmWanMbusA3 62 }

hmWanMbusA3Value1C		OBJECT-TYPE
			SYNTAX	INTEGER
			MAX-ACCESS	read-only
			STATUS	current
			::= { hmWanMbusA3 63 }

hmWanMbusA3VIF1D		OBJECT-TYPE
			SYNTAX	INTEGER
			MAX-ACCESS	read-only
			STATUS	current
			::= { hmWanMbusA3 64 }

hmWanMbusA3Value1D		OBJECT-TYPE
			SYNTAX	INTEGER
			MAX-ACCESS	read-only
			STATUS	current
			::= { hmWanMbusA3 65 }

hmWanMbusA3VIF1E		OBJECT-TYPE
			SYNTAX	INTEGER
			MAX-ACCESS	read-only
			STATUS	current
			::= { hmWanMbusA3 66 }

hmWanMbusA3Value1E		OBJECT-TYPE
			SYNTAX	INTEGER
			MAX-ACCESS	read-only
			STATUS	current
			::= { hmWanMbusA3 67 }

hmWanMbusA3VIF1F		OBJECT-TYPE
			SYNTAX	INTEGER
			MAX-ACCESS	read-only
			STATUS	current
			::= { hmWanMbusA3 68 }

hmWanMbusA3Value1F		OBJECT-TYPE
			SYNTAX	INTEGER
			MAX-ACCESS	read-only
			STATUS	current
			::= { hmWanMbusA3 69 }

hmWanMbusA3VIF20		OBJECT-TYPE
			SYNTAX	INTEGER
			MAX-ACCESS	read-only
			STATUS	current
			::= { hmWanMbusA3 70 }

hmWanMbusA3Value20		OBJECT-TYPE
			SYNTAX	INTEGER
			MAX-ACCESS	read-only
			STATUS	current
			::= { hmWanMbusA3 71 }

hmWanMbusA3VIF21		OBJECT-TYPE
			SYNTAX	INTEGER
			MAX-ACCESS	read-only
			STATUS	current
			::= { hmWanMbusA3 72 }

hmWanMbusA3Value21		OBJECT-TYPE
			SYNTAX	INTEGER
			MAX-ACCESS	read-only
			STATUS	current
			::= { hmWanMbusA3 73 }

hmWanMbusA3VIF22		OBJECT-TYPE
			SYNTAX	INTEGER
			MAX-ACCESS	read-only
			STATUS	current
			::= { hmWanMbusA3 74 }

hmWanMbusA3Value22		OBJECT-TYPE
			SYNTAX	INTEGER
			MAX-ACCESS	read-only
			STATUS	current
			::= { hmWanMbusA3 75 }

hmWanMbusA3VIF23		OBJECT-TYPE
			SYNTAX	INTEGER
			MAX-ACCESS	read-only
			STATUS	current
			::= { hmWanMbusA3 76 }

hmWanMbusA3Value23		OBJECT-TYPE
			SYNTAX	INTEGER
			MAX-ACCESS	read-only
			STATUS	current
			::= { hmWanMbusA3 77 }

hmWanMbusA3VIF24		OBJECT-TYPE
			SYNTAX	INTEGER
			MAX-ACCESS	read-only
			STATUS	current
			::= { hmWanMbusA3 78 }

hmWanMbusA3Value24		OBJECT-TYPE
			SYNTAX	INTEGER
			MAX-ACCESS	read-only
			STATUS	current
			::= { hmWanMbusA3 79 }

hmWanMbusA3VIF25		OBJECT-TYPE
			SYNTAX	INTEGER
			MAX-ACCESS	read-only
			STATUS	current
			::= { hmWanMbusA3 80 }

hmWanMbusA3Value25		OBJECT-TYPE
			SYNTAX	INTEGER
			MAX-ACCESS	read-only
			STATUS	current
			::= { hmWanMbusA3 81 }

hmWanMbusA3VIF26		OBJECT-TYPE
			SYNTAX	INTEGER
			MAX-ACCESS	read-only
			STATUS	current
			::= { hmWanMbusA3 82 }

hmWanMbusA3Value26		OBJECT-TYPE
			SYNTAX	INTEGER
			MAX-ACCESS	read-only
			STATUS	current
			::= { hmWanMbusA3 83 }

hmWanMbusA3VIF27		OBJECT-TYPE
			SYNTAX	INTEGER
			MAX-ACCESS	read-only
			STATUS	current
			::= { hmWanMbusA3 84 }

hmWanMbusA3Value27		OBJECT-TYPE
			SYNTAX	INTEGER
			MAX-ACCESS	read-only
			STATUS	current
			::= { hmWanMbusA3 85 }

hmWanMbusA3VIF28		OBJECT-TYPE
			SYNTAX	INTEGER
			MAX-ACCESS	read-only
			STATUS	current
			::= { hmWanMbusA3 86 }

hmWanMbusA3Value28		OBJECT-TYPE
			SYNTAX	INTEGER
			MAX-ACCESS	read-only
			STATUS	current
			::= { hmWanMbusA3 87 }

hmWanMbusA3VIF29		OBJECT-TYPE
			SYNTAX	INTEGER
			MAX-ACCESS	read-only
			STATUS	current
			::= { hmWanMbusA3 88 }

hmWanMbusA3Value29		OBJECT-TYPE
			SYNTAX	INTEGER
			MAX-ACCESS	read-only
			STATUS	current
			::= { hmWanMbusA3 89 }

hmWanMbusA3VIF2A		OBJECT-TYPE
			SYNTAX	INTEGER
			MAX-ACCESS	read-only
			STATUS	current
			::= { hmWanMbusA3 90 }

hmWanMbusA3Value2A		OBJECT-TYPE
			SYNTAX	INTEGER
			MAX-ACCESS	read-only
			STATUS	current
			::= { hmWanMbusA3 91 }

hmWanMbusA3VIF2B		OBJECT-TYPE
			SYNTAX	INTEGER
			MAX-ACCESS	read-only
			STATUS	current
			::= { hmWanMbusA3 92 }

hmWanMbusA3Value2B		OBJECT-TYPE
			SYNTAX	INTEGER
			MAX-ACCESS	read-only
			STATUS	current
			::= { hmWanMbusA3 93 }

hmWanMbusA3VIF2C		OBJECT-TYPE
			SYNTAX	INTEGER
			MAX-ACCESS	read-only
			STATUS	current
			::= { hmWanMbusA3 94 }

hmWanMbusA3Value2C		OBJECT-TYPE
			SYNTAX	INTEGER
			MAX-ACCESS	read-only
			STATUS	current
			::= { hmWanMbusA3 95 }

hmWanMbusA3VIF2D		OBJECT-TYPE
			SYNTAX	INTEGER
			MAX-ACCESS	read-only
			STATUS	current
			::= { hmWanMbusA3 96 }

hmWanMbusA3Value2D		OBJECT-TYPE
			SYNTAX	INTEGER
			MAX-ACCESS	read-only
			STATUS	current
			::= { hmWanMbusA3 97 }

hmWanMbusA3VIF2E		OBJECT-TYPE
			SYNTAX	INTEGER
			MAX-ACCESS	read-only
			STATUS	current
			::= { hmWanMbusA3 98 }

hmWanMbusA3Value2E		OBJECT-TYPE
			SYNTAX	INTEGER
			MAX-ACCESS	read-only
			STATUS	current
			::= { hmWanMbusA3 99 }

hmWanMbusA3VIF2F		OBJECT-TYPE
			SYNTAX	INTEGER
			MAX-ACCESS	read-only
			STATUS	current
			::= { hmWanMbusA3 100 }

hmWanMbusA3Value2F		OBJECT-TYPE
			SYNTAX	INTEGER
			MAX-ACCESS	read-only
			STATUS	current
			::= { hmWanMbusA3 101 }

hmWanMbusA4			OBJECT IDENTIFIER ::= { hmWanMbus 164 }

hmWanMbusA4IdNumber		OBJECT-TYPE
			SYNTAX	Gauge32
			MAX-ACCESS	read-only
			STATUS	current
			::= { hmWanMbusA4 1 }

hmWanMbusA4Manufacturer	OBJECT-TYPE
			SYNTAX	Gauge32
			MAX-ACCESS	read-only
			STATUS	current
			::= { hmWanMbusA4 2 }

hmWanMbusA4Version		OBJECT-TYPE
			SYNTAX	Gauge32
			MAX-ACCESS	read-only
			STATUS	current
			::= { hmWanMbusA4 3 }

hmWanMbusA4Medium		OBJECT-TYPE
			SYNTAX	Gauge32
			MAX-ACCESS	read-only
			STATUS	current
			::= { hmWanMbusA4 4 }

hmWanMbusA4Status		OBJECT-TYPE
			SYNTAX	Gauge32
			MAX-ACCESS	read-only
			STATUS	current
			::= { hmWanMbusA4 5 }

hmWanMbusA4VIF00		OBJECT-TYPE
			SYNTAX	INTEGER
			MAX-ACCESS	read-only
			STATUS	current
			::= { hmWanMbusA4 6 }

hmWanMbusA4Value00		OBJECT-TYPE
			SYNTAX	INTEGER
			MAX-ACCESS	read-only
			STATUS	current
			::= { hmWanMbusA4 7 }

hmWanMbusA4VIF01		OBJECT-TYPE
			SYNTAX	INTEGER
			MAX-ACCESS	read-only
			STATUS	current
			::= { hmWanMbusA4 8 }

hmWanMbusA4Value01		OBJECT-TYPE
			SYNTAX	INTEGER
			MAX-ACCESS	read-only
			STATUS	current
			::= { hmWanMbusA4 9 }

hmWanMbusA4VIF02		OBJECT-TYPE
			SYNTAX	INTEGER
			MAX-ACCESS	read-only
			STATUS	current
			::= { hmWanMbusA4 10 }

hmWanMbusA4Value02		OBJECT-TYPE
			SYNTAX	INTEGER
			MAX-ACCESS	read-only
			STATUS	current
			::= { hmWanMbusA4 11 }

hmWanMbusA4VIF03		OBJECT-TYPE
			SYNTAX	INTEGER
			MAX-ACCESS	read-only
			STATUS	current
			::= { hmWanMbusA4 12 }

hmWanMbusA4Value03		OBJECT-TYPE
			SYNTAX	INTEGER
			MAX-ACCESS	read-only
			STATUS	current
			::= { hmWanMbusA4 13 }

hmWanMbusA4VIF04		OBJECT-TYPE
			SYNTAX	INTEGER
			MAX-ACCESS	read-only
			STATUS	current
			::= { hmWanMbusA4 14 }

hmWanMbusA4Value04		OBJECT-TYPE
			SYNTAX	INTEGER
			MAX-ACCESS	read-only
			STATUS	current
			::= { hmWanMbusA4 15 }

hmWanMbusA4VIF05		OBJECT-TYPE
			SYNTAX	INTEGER
			MAX-ACCESS	read-only
			STATUS	current
			::= { hmWanMbusA4 16 }

hmWanMbusA4Value05		OBJECT-TYPE
			SYNTAX	INTEGER
			MAX-ACCESS	read-only
			STATUS	current
			::= { hmWanMbusA4 17 }

hmWanMbusA4VIF06		OBJECT-TYPE
			SYNTAX	INTEGER
			MAX-ACCESS	read-only
			STATUS	current
			::= { hmWanMbusA4 18 }

hmWanMbusA4Value06		OBJECT-TYPE
			SYNTAX	INTEGER
			MAX-ACCESS	read-only
			STATUS	current
			::= { hmWanMbusA4 19 }

hmWanMbusA4VIF07		OBJECT-TYPE
			SYNTAX	INTEGER
			MAX-ACCESS	read-only
			STATUS	current
			::= { hmWanMbusA4 20 }

hmWanMbusA4Value07		OBJECT-TYPE
			SYNTAX	INTEGER
			MAX-ACCESS	read-only
			STATUS	current
			::= { hmWanMbusA4 21 }

hmWanMbusA4VIF08		OBJECT-TYPE
			SYNTAX	INTEGER
			MAX-ACCESS	read-only
			STATUS	current
			::= { hmWanMbusA4 22 }

hmWanMbusA4Value08		OBJECT-TYPE
			SYNTAX	INTEGER
			MAX-ACCESS	read-only
			STATUS	current
			::= { hmWanMbusA4 23 }

hmWanMbusA4VIF09		OBJECT-TYPE
			SYNTAX	INTEGER
			MAX-ACCESS	read-only
			STATUS	current
			::= { hmWanMbusA4 24 }

hmWanMbusA4Value09		OBJECT-TYPE
			SYNTAX	INTEGER
			MAX-ACCESS	read-only
			STATUS	current
			::= { hmWanMbusA4 25 }

hmWanMbusA4VIF0A		OBJECT-TYPE
			SYNTAX	INTEGER
			MAX-ACCESS	read-only
			STATUS	current
			::= { hmWanMbusA4 26 }

hmWanMbusA4Value0A		OBJECT-TYPE
			SYNTAX	INTEGER
			MAX-ACCESS	read-only
			STATUS	current
			::= { hmWanMbusA4 27 }

hmWanMbusA4VIF0B		OBJECT-TYPE
			SYNTAX	INTEGER
			MAX-ACCESS	read-only
			STATUS	current
			::= { hmWanMbusA4 28 }

hmWanMbusA4Value0B		OBJECT-TYPE
			SYNTAX	INTEGER
			MAX-ACCESS	read-only
			STATUS	current
			::= { hmWanMbusA4 29 }

hmWanMbusA4VIF0C		OBJECT-TYPE
			SYNTAX	INTEGER
			MAX-ACCESS	read-only
			STATUS	current
			::= { hmWanMbusA4 30 }

hmWanMbusA4Value0C		OBJECT-TYPE
			SYNTAX	INTEGER
			MAX-ACCESS	read-only
			STATUS	current
			::= { hmWanMbusA4 31 }

hmWanMbusA4VIF0D		OBJECT-TYPE
			SYNTAX	INTEGER
			MAX-ACCESS	read-only
			STATUS	current
			::= { hmWanMbusA4 32 }

hmWanMbusA4Value0D		OBJECT-TYPE
			SYNTAX	INTEGER
			MAX-ACCESS	read-only
			STATUS	current
			::= { hmWanMbusA4 33 }

hmWanMbusA4VIF0E		OBJECT-TYPE
			SYNTAX	INTEGER
			MAX-ACCESS	read-only
			STATUS	current
			::= { hmWanMbusA4 34 }

hmWanMbusA4Value0E		OBJECT-TYPE
			SYNTAX	INTEGER
			MAX-ACCESS	read-only
			STATUS	current
			::= { hmWanMbusA4 35 }

hmWanMbusA4VIF0F		OBJECT-TYPE
			SYNTAX	INTEGER
			MAX-ACCESS	read-only
			STATUS	current
			::= { hmWanMbusA4 36 }

hmWanMbusA4Value0F		OBJECT-TYPE
			SYNTAX	INTEGER
			MAX-ACCESS	read-only
			STATUS	current
			::= { hmWanMbusA4 37 }

hmWanMbusA4VIF10		OBJECT-TYPE
			SYNTAX	INTEGER
			MAX-ACCESS	read-only
			STATUS	current
			::= { hmWanMbusA4 38 }

hmWanMbusA4Value10		OBJECT-TYPE
			SYNTAX	INTEGER
			MAX-ACCESS	read-only
			STATUS	current
			::= { hmWanMbusA4 39 }

hmWanMbusA4VIF11		OBJECT-TYPE
			SYNTAX	INTEGER
			MAX-ACCESS	read-only
			STATUS	current
			::= { hmWanMbusA4 40 }

hmWanMbusA4Value11		OBJECT-TYPE
			SYNTAX	INTEGER
			MAX-ACCESS	read-only
			STATUS	current
			::= { hmWanMbusA4 41 }

hmWanMbusA4VIF12		OBJECT-TYPE
			SYNTAX	INTEGER
			MAX-ACCESS	read-only
			STATUS	current
			::= { hmWanMbusA4 42 }

hmWanMbusA4Value12		OBJECT-TYPE
			SYNTAX	INTEGER
			MAX-ACCESS	read-only
			STATUS	current
			::= { hmWanMbusA4 43 }

hmWanMbusA4VIF13		OBJECT-TYPE
			SYNTAX	INTEGER
			MAX-ACCESS	read-only
			STATUS	current
			::= { hmWanMbusA4 44 }

hmWanMbusA4Value13		OBJECT-TYPE
			SYNTAX	INTEGER
			MAX-ACCESS	read-only
			STATUS	current
			::= { hmWanMbusA4 45 }

hmWanMbusA4VIF14		OBJECT-TYPE
			SYNTAX	INTEGER
			MAX-ACCESS	read-only
			STATUS	current
			::= { hmWanMbusA4 46 }

hmWanMbusA4Value14		OBJECT-TYPE
			SYNTAX	INTEGER
			MAX-ACCESS	read-only
			STATUS	current
			::= { hmWanMbusA4 47 }

hmWanMbusA4VIF15		OBJECT-TYPE
			SYNTAX	INTEGER
			MAX-ACCESS	read-only
			STATUS	current
			::= { hmWanMbusA4 48 }

hmWanMbusA4Value15		OBJECT-TYPE
			SYNTAX	INTEGER
			MAX-ACCESS	read-only
			STATUS	current
			::= { hmWanMbusA4 49 }

hmWanMbusA4VIF16		OBJECT-TYPE
			SYNTAX	INTEGER
			MAX-ACCESS	read-only
			STATUS	current
			::= { hmWanMbusA4 50 }

hmWanMbusA4Value16		OBJECT-TYPE
			SYNTAX	INTEGER
			MAX-ACCESS	read-only
			STATUS	current
			::= { hmWanMbusA4 51 }

hmWanMbusA4VIF17		OBJECT-TYPE
			SYNTAX	INTEGER
			MAX-ACCESS	read-only
			STATUS	current
			::= { hmWanMbusA4 52 }

hmWanMbusA4Value17		OBJECT-TYPE
			SYNTAX	INTEGER
			MAX-ACCESS	read-only
			STATUS	current
			::= { hmWanMbusA4 53 }

hmWanMbusA4VIF18		OBJECT-TYPE
			SYNTAX	INTEGER
			MAX-ACCESS	read-only
			STATUS	current
			::= { hmWanMbusA4 54 }

hmWanMbusA4Value18		OBJECT-TYPE
			SYNTAX	INTEGER
			MAX-ACCESS	read-only
			STATUS	current
			::= { hmWanMbusA4 55 }

hmWanMbusA4VIF19		OBJECT-TYPE
			SYNTAX	INTEGER
			MAX-ACCESS	read-only
			STATUS	current
			::= { hmWanMbusA4 56 }

hmWanMbusA4Value19		OBJECT-TYPE
			SYNTAX	INTEGER
			MAX-ACCESS	read-only
			STATUS	current
			::= { hmWanMbusA4 57 }

hmWanMbusA4VIF1A		OBJECT-TYPE
			SYNTAX	INTEGER
			MAX-ACCESS	read-only
			STATUS	current
			::= { hmWanMbusA4 58 }

hmWanMbusA4Value1A		OBJECT-TYPE
			SYNTAX	INTEGER
			MAX-ACCESS	read-only
			STATUS	current
			::= { hmWanMbusA4 59 }

hmWanMbusA4VIF1B		OBJECT-TYPE
			SYNTAX	INTEGER
			MAX-ACCESS	read-only
			STATUS	current
			::= { hmWanMbusA4 60 }

hmWanMbusA4Value1B		OBJECT-TYPE
			SYNTAX	INTEGER
			MAX-ACCESS	read-only
			STATUS	current
			::= { hmWanMbusA4 61 }

hmWanMbusA4VIF1C		OBJECT-TYPE
			SYNTAX	INTEGER
			MAX-ACCESS	read-only
			STATUS	current
			::= { hmWanMbusA4 62 }

hmWanMbusA4Value1C		OBJECT-TYPE
			SYNTAX	INTEGER
			MAX-ACCESS	read-only
			STATUS	current
			::= { hmWanMbusA4 63 }

hmWanMbusA4VIF1D		OBJECT-TYPE
			SYNTAX	INTEGER
			MAX-ACCESS	read-only
			STATUS	current
			::= { hmWanMbusA4 64 }

hmWanMbusA4Value1D		OBJECT-TYPE
			SYNTAX	INTEGER
			MAX-ACCESS	read-only
			STATUS	current
			::= { hmWanMbusA4 65 }

hmWanMbusA4VIF1E		OBJECT-TYPE
			SYNTAX	INTEGER
			MAX-ACCESS	read-only
			STATUS	current
			::= { hmWanMbusA4 66 }

hmWanMbusA4Value1E		OBJECT-TYPE
			SYNTAX	INTEGER
			MAX-ACCESS	read-only
			STATUS	current
			::= { hmWanMbusA4 67 }

hmWanMbusA4VIF1F		OBJECT-TYPE
			SYNTAX	INTEGER
			MAX-ACCESS	read-only
			STATUS	current
			::= { hmWanMbusA4 68 }

hmWanMbusA4Value1F		OBJECT-TYPE
			SYNTAX	INTEGER
			MAX-ACCESS	read-only
			STATUS	current
			::= { hmWanMbusA4 69 }

hmWanMbusA4VIF20		OBJECT-TYPE
			SYNTAX	INTEGER
			MAX-ACCESS	read-only
			STATUS	current
			::= { hmWanMbusA4 70 }

hmWanMbusA4Value20		OBJECT-TYPE
			SYNTAX	INTEGER
			MAX-ACCESS	read-only
			STATUS	current
			::= { hmWanMbusA4 71 }

hmWanMbusA4VIF21		OBJECT-TYPE
			SYNTAX	INTEGER
			MAX-ACCESS	read-only
			STATUS	current
			::= { hmWanMbusA4 72 }

hmWanMbusA4Value21		OBJECT-TYPE
			SYNTAX	INTEGER
			MAX-ACCESS	read-only
			STATUS	current
			::= { hmWanMbusA4 73 }

hmWanMbusA4VIF22		OBJECT-TYPE
			SYNTAX	INTEGER
			MAX-ACCESS	read-only
			STATUS	current
			::= { hmWanMbusA4 74 }

hmWanMbusA4Value22		OBJECT-TYPE
			SYNTAX	INTEGER
			MAX-ACCESS	read-only
			STATUS	current
			::= { hmWanMbusA4 75 }

hmWanMbusA4VIF23		OBJECT-TYPE
			SYNTAX	INTEGER
			MAX-ACCESS	read-only
			STATUS	current
			::= { hmWanMbusA4 76 }

hmWanMbusA4Value23		OBJECT-TYPE
			SYNTAX	INTEGER
			MAX-ACCESS	read-only
			STATUS	current
			::= { hmWanMbusA4 77 }

hmWanMbusA4VIF24		OBJECT-TYPE
			SYNTAX	INTEGER
			MAX-ACCESS	read-only
			STATUS	current
			::= { hmWanMbusA4 78 }

hmWanMbusA4Value24		OBJECT-TYPE
			SYNTAX	INTEGER
			MAX-ACCESS	read-only
			STATUS	current
			::= { hmWanMbusA4 79 }

hmWanMbusA4VIF25		OBJECT-TYPE
			SYNTAX	INTEGER
			MAX-ACCESS	read-only
			STATUS	current
			::= { hmWanMbusA4 80 }

hmWanMbusA4Value25		OBJECT-TYPE
			SYNTAX	INTEGER
			MAX-ACCESS	read-only
			STATUS	current
			::= { hmWanMbusA4 81 }

hmWanMbusA4VIF26		OBJECT-TYPE
			SYNTAX	INTEGER
			MAX-ACCESS	read-only
			STATUS	current
			::= { hmWanMbusA4 82 }

hmWanMbusA4Value26		OBJECT-TYPE
			SYNTAX	INTEGER
			MAX-ACCESS	read-only
			STATUS	current
			::= { hmWanMbusA4 83 }

hmWanMbusA4VIF27		OBJECT-TYPE
			SYNTAX	INTEGER
			MAX-ACCESS	read-only
			STATUS	current
			::= { hmWanMbusA4 84 }

hmWanMbusA4Value27		OBJECT-TYPE
			SYNTAX	INTEGER
			MAX-ACCESS	read-only
			STATUS	current
			::= { hmWanMbusA4 85 }

hmWanMbusA4VIF28		OBJECT-TYPE
			SYNTAX	INTEGER
			MAX-ACCESS	read-only
			STATUS	current
			::= { hmWanMbusA4 86 }

hmWanMbusA4Value28		OBJECT-TYPE
			SYNTAX	INTEGER
			MAX-ACCESS	read-only
			STATUS	current
			::= { hmWanMbusA4 87 }

hmWanMbusA4VIF29		OBJECT-TYPE
			SYNTAX	INTEGER
			MAX-ACCESS	read-only
			STATUS	current
			::= { hmWanMbusA4 88 }

hmWanMbusA4Value29		OBJECT-TYPE
			SYNTAX	INTEGER
			MAX-ACCESS	read-only
			STATUS	current
			::= { hmWanMbusA4 89 }

hmWanMbusA4VIF2A		OBJECT-TYPE
			SYNTAX	INTEGER
			MAX-ACCESS	read-only
			STATUS	current
			::= { hmWanMbusA4 90 }

hmWanMbusA4Value2A		OBJECT-TYPE
			SYNTAX	INTEGER
			MAX-ACCESS	read-only
			STATUS	current
			::= { hmWanMbusA4 91 }

hmWanMbusA4VIF2B		OBJECT-TYPE
			SYNTAX	INTEGER
			MAX-ACCESS	read-only
			STATUS	current
			::= { hmWanMbusA4 92 }

hmWanMbusA4Value2B		OBJECT-TYPE
			SYNTAX	INTEGER
			MAX-ACCESS	read-only
			STATUS	current
			::= { hmWanMbusA4 93 }

hmWanMbusA4VIF2C		OBJECT-TYPE
			SYNTAX	INTEGER
			MAX-ACCESS	read-only
			STATUS	current
			::= { hmWanMbusA4 94 }

hmWanMbusA4Value2C		OBJECT-TYPE
			SYNTAX	INTEGER
			MAX-ACCESS	read-only
			STATUS	current
			::= { hmWanMbusA4 95 }

hmWanMbusA4VIF2D		OBJECT-TYPE
			SYNTAX	INTEGER
			MAX-ACCESS	read-only
			STATUS	current
			::= { hmWanMbusA4 96 }

hmWanMbusA4Value2D		OBJECT-TYPE
			SYNTAX	INTEGER
			MAX-ACCESS	read-only
			STATUS	current
			::= { hmWanMbusA4 97 }

hmWanMbusA4VIF2E		OBJECT-TYPE
			SYNTAX	INTEGER
			MAX-ACCESS	read-only
			STATUS	current
			::= { hmWanMbusA4 98 }

hmWanMbusA4Value2E		OBJECT-TYPE
			SYNTAX	INTEGER
			MAX-ACCESS	read-only
			STATUS	current
			::= { hmWanMbusA4 99 }

hmWanMbusA4VIF2F		OBJECT-TYPE
			SYNTAX	INTEGER
			MAX-ACCESS	read-only
			STATUS	current
			::= { hmWanMbusA4 100 }

hmWanMbusA4Value2F		OBJECT-TYPE
			SYNTAX	INTEGER
			MAX-ACCESS	read-only
			STATUS	current
			::= { hmWanMbusA4 101 }

hmWanMbusA5			OBJECT IDENTIFIER ::= { hmWanMbus 165 }

hmWanMbusA5IdNumber		OBJECT-TYPE
			SYNTAX	Gauge32
			MAX-ACCESS	read-only
			STATUS	current
			::= { hmWanMbusA5 1 }

hmWanMbusA5Manufacturer	OBJECT-TYPE
			SYNTAX	Gauge32
			MAX-ACCESS	read-only
			STATUS	current
			::= { hmWanMbusA5 2 }

hmWanMbusA5Version		OBJECT-TYPE
			SYNTAX	Gauge32
			MAX-ACCESS	read-only
			STATUS	current
			::= { hmWanMbusA5 3 }

hmWanMbusA5Medium		OBJECT-TYPE
			SYNTAX	Gauge32
			MAX-ACCESS	read-only
			STATUS	current
			::= { hmWanMbusA5 4 }

hmWanMbusA5Status		OBJECT-TYPE
			SYNTAX	Gauge32
			MAX-ACCESS	read-only
			STATUS	current
			::= { hmWanMbusA5 5 }

hmWanMbusA5VIF00		OBJECT-TYPE
			SYNTAX	INTEGER
			MAX-ACCESS	read-only
			STATUS	current
			::= { hmWanMbusA5 6 }

hmWanMbusA5Value00		OBJECT-TYPE
			SYNTAX	INTEGER
			MAX-ACCESS	read-only
			STATUS	current
			::= { hmWanMbusA5 7 }

hmWanMbusA5VIF01		OBJECT-TYPE
			SYNTAX	INTEGER
			MAX-ACCESS	read-only
			STATUS	current
			::= { hmWanMbusA5 8 }

hmWanMbusA5Value01		OBJECT-TYPE
			SYNTAX	INTEGER
			MAX-ACCESS	read-only
			STATUS	current
			::= { hmWanMbusA5 9 }

hmWanMbusA5VIF02		OBJECT-TYPE
			SYNTAX	INTEGER
			MAX-ACCESS	read-only
			STATUS	current
			::= { hmWanMbusA5 10 }

hmWanMbusA5Value02		OBJECT-TYPE
			SYNTAX	INTEGER
			MAX-ACCESS	read-only
			STATUS	current
			::= { hmWanMbusA5 11 }

hmWanMbusA5VIF03		OBJECT-TYPE
			SYNTAX	INTEGER
			MAX-ACCESS	read-only
			STATUS	current
			::= { hmWanMbusA5 12 }

hmWanMbusA5Value03		OBJECT-TYPE
			SYNTAX	INTEGER
			MAX-ACCESS	read-only
			STATUS	current
			::= { hmWanMbusA5 13 }

hmWanMbusA5VIF04		OBJECT-TYPE
			SYNTAX	INTEGER
			MAX-ACCESS	read-only
			STATUS	current
			::= { hmWanMbusA5 14 }

hmWanMbusA5Value04		OBJECT-TYPE
			SYNTAX	INTEGER
			MAX-ACCESS	read-only
			STATUS	current
			::= { hmWanMbusA5 15 }

hmWanMbusA5VIF05		OBJECT-TYPE
			SYNTAX	INTEGER
			MAX-ACCESS	read-only
			STATUS	current
			::= { hmWanMbusA5 16 }

hmWanMbusA5Value05		OBJECT-TYPE
			SYNTAX	INTEGER
			MAX-ACCESS	read-only
			STATUS	current
			::= { hmWanMbusA5 17 }

hmWanMbusA5VIF06		OBJECT-TYPE
			SYNTAX	INTEGER
			MAX-ACCESS	read-only
			STATUS	current
			::= { hmWanMbusA5 18 }

hmWanMbusA5Value06		OBJECT-TYPE
			SYNTAX	INTEGER
			MAX-ACCESS	read-only
			STATUS	current
			::= { hmWanMbusA5 19 }

hmWanMbusA5VIF07		OBJECT-TYPE
			SYNTAX	INTEGER
			MAX-ACCESS	read-only
			STATUS	current
			::= { hmWanMbusA5 20 }

hmWanMbusA5Value07		OBJECT-TYPE
			SYNTAX	INTEGER
			MAX-ACCESS	read-only
			STATUS	current
			::= { hmWanMbusA5 21 }

hmWanMbusA5VIF08		OBJECT-TYPE
			SYNTAX	INTEGER
			MAX-ACCESS	read-only
			STATUS	current
			::= { hmWanMbusA5 22 }

hmWanMbusA5Value08		OBJECT-TYPE
			SYNTAX	INTEGER
			MAX-ACCESS	read-only
			STATUS	current
			::= { hmWanMbusA5 23 }

hmWanMbusA5VIF09		OBJECT-TYPE
			SYNTAX	INTEGER
			MAX-ACCESS	read-only
			STATUS	current
			::= { hmWanMbusA5 24 }

hmWanMbusA5Value09		OBJECT-TYPE
			SYNTAX	INTEGER
			MAX-ACCESS	read-only
			STATUS	current
			::= { hmWanMbusA5 25 }

hmWanMbusA5VIF0A		OBJECT-TYPE
			SYNTAX	INTEGER
			MAX-ACCESS	read-only
			STATUS	current
			::= { hmWanMbusA5 26 }

hmWanMbusA5Value0A		OBJECT-TYPE
			SYNTAX	INTEGER
			MAX-ACCESS	read-only
			STATUS	current
			::= { hmWanMbusA5 27 }

hmWanMbusA5VIF0B		OBJECT-TYPE
			SYNTAX	INTEGER
			MAX-ACCESS	read-only
			STATUS	current
			::= { hmWanMbusA5 28 }

hmWanMbusA5Value0B		OBJECT-TYPE
			SYNTAX	INTEGER
			MAX-ACCESS	read-only
			STATUS	current
			::= { hmWanMbusA5 29 }

hmWanMbusA5VIF0C		OBJECT-TYPE
			SYNTAX	INTEGER
			MAX-ACCESS	read-only
			STATUS	current
			::= { hmWanMbusA5 30 }

hmWanMbusA5Value0C		OBJECT-TYPE
			SYNTAX	INTEGER
			MAX-ACCESS	read-only
			STATUS	current
			::= { hmWanMbusA5 31 }

hmWanMbusA5VIF0D		OBJECT-TYPE
			SYNTAX	INTEGER
			MAX-ACCESS	read-only
			STATUS	current
			::= { hmWanMbusA5 32 }

hmWanMbusA5Value0D		OBJECT-TYPE
			SYNTAX	INTEGER
			MAX-ACCESS	read-only
			STATUS	current
			::= { hmWanMbusA5 33 }

hmWanMbusA5VIF0E		OBJECT-TYPE
			SYNTAX	INTEGER
			MAX-ACCESS	read-only
			STATUS	current
			::= { hmWanMbusA5 34 }

hmWanMbusA5Value0E		OBJECT-TYPE
			SYNTAX	INTEGER
			MAX-ACCESS	read-only
			STATUS	current
			::= { hmWanMbusA5 35 }

hmWanMbusA5VIF0F		OBJECT-TYPE
			SYNTAX	INTEGER
			MAX-ACCESS	read-only
			STATUS	current
			::= { hmWanMbusA5 36 }

hmWanMbusA5Value0F		OBJECT-TYPE
			SYNTAX	INTEGER
			MAX-ACCESS	read-only
			STATUS	current
			::= { hmWanMbusA5 37 }

hmWanMbusA5VIF10		OBJECT-TYPE
			SYNTAX	INTEGER
			MAX-ACCESS	read-only
			STATUS	current
			::= { hmWanMbusA5 38 }

hmWanMbusA5Value10		OBJECT-TYPE
			SYNTAX	INTEGER
			MAX-ACCESS	read-only
			STATUS	current
			::= { hmWanMbusA5 39 }

hmWanMbusA5VIF11		OBJECT-TYPE
			SYNTAX	INTEGER
			MAX-ACCESS	read-only
			STATUS	current
			::= { hmWanMbusA5 40 }

hmWanMbusA5Value11		OBJECT-TYPE
			SYNTAX	INTEGER
			MAX-ACCESS	read-only
			STATUS	current
			::= { hmWanMbusA5 41 }

hmWanMbusA5VIF12		OBJECT-TYPE
			SYNTAX	INTEGER
			MAX-ACCESS	read-only
			STATUS	current
			::= { hmWanMbusA5 42 }

hmWanMbusA5Value12		OBJECT-TYPE
			SYNTAX	INTEGER
			MAX-ACCESS	read-only
			STATUS	current
			::= { hmWanMbusA5 43 }

hmWanMbusA5VIF13		OBJECT-TYPE
			SYNTAX	INTEGER
			MAX-ACCESS	read-only
			STATUS	current
			::= { hmWanMbusA5 44 }

hmWanMbusA5Value13		OBJECT-TYPE
			SYNTAX	INTEGER
			MAX-ACCESS	read-only
			STATUS	current
			::= { hmWanMbusA5 45 }

hmWanMbusA5VIF14		OBJECT-TYPE
			SYNTAX	INTEGER
			MAX-ACCESS	read-only
			STATUS	current
			::= { hmWanMbusA5 46 }

hmWanMbusA5Value14		OBJECT-TYPE
			SYNTAX	INTEGER
			MAX-ACCESS	read-only
			STATUS	current
			::= { hmWanMbusA5 47 }

hmWanMbusA5VIF15		OBJECT-TYPE
			SYNTAX	INTEGER
			MAX-ACCESS	read-only
			STATUS	current
			::= { hmWanMbusA5 48 }

hmWanMbusA5Value15		OBJECT-TYPE
			SYNTAX	INTEGER
			MAX-ACCESS	read-only
			STATUS	current
			::= { hmWanMbusA5 49 }

hmWanMbusA5VIF16		OBJECT-TYPE
			SYNTAX	INTEGER
			MAX-ACCESS	read-only
			STATUS	current
			::= { hmWanMbusA5 50 }

hmWanMbusA5Value16		OBJECT-TYPE
			SYNTAX	INTEGER
			MAX-ACCESS	read-only
			STATUS	current
			::= { hmWanMbusA5 51 }

hmWanMbusA5VIF17		OBJECT-TYPE
			SYNTAX	INTEGER
			MAX-ACCESS	read-only
			STATUS	current
			::= { hmWanMbusA5 52 }

hmWanMbusA5Value17		OBJECT-TYPE
			SYNTAX	INTEGER
			MAX-ACCESS	read-only
			STATUS	current
			::= { hmWanMbusA5 53 }

hmWanMbusA5VIF18		OBJECT-TYPE
			SYNTAX	INTEGER
			MAX-ACCESS	read-only
			STATUS	current
			::= { hmWanMbusA5 54 }

hmWanMbusA5Value18		OBJECT-TYPE
			SYNTAX	INTEGER
			MAX-ACCESS	read-only
			STATUS	current
			::= { hmWanMbusA5 55 }

hmWanMbusA5VIF19		OBJECT-TYPE
			SYNTAX	INTEGER
			MAX-ACCESS	read-only
			STATUS	current
			::= { hmWanMbusA5 56 }

hmWanMbusA5Value19		OBJECT-TYPE
			SYNTAX	INTEGER
			MAX-ACCESS	read-only
			STATUS	current
			::= { hmWanMbusA5 57 }

hmWanMbusA5VIF1A		OBJECT-TYPE
			SYNTAX	INTEGER
			MAX-ACCESS	read-only
			STATUS	current
			::= { hmWanMbusA5 58 }

hmWanMbusA5Value1A		OBJECT-TYPE
			SYNTAX	INTEGER
			MAX-ACCESS	read-only
			STATUS	current
			::= { hmWanMbusA5 59 }

hmWanMbusA5VIF1B		OBJECT-TYPE
			SYNTAX	INTEGER
			MAX-ACCESS	read-only
			STATUS	current
			::= { hmWanMbusA5 60 }

hmWanMbusA5Value1B		OBJECT-TYPE
			SYNTAX	INTEGER
			MAX-ACCESS	read-only
			STATUS	current
			::= { hmWanMbusA5 61 }

hmWanMbusA5VIF1C		OBJECT-TYPE
			SYNTAX	INTEGER
			MAX-ACCESS	read-only
			STATUS	current
			::= { hmWanMbusA5 62 }

hmWanMbusA5Value1C		OBJECT-TYPE
			SYNTAX	INTEGER
			MAX-ACCESS	read-only
			STATUS	current
			::= { hmWanMbusA5 63 }

hmWanMbusA5VIF1D		OBJECT-TYPE
			SYNTAX	INTEGER
			MAX-ACCESS	read-only
			STATUS	current
			::= { hmWanMbusA5 64 }

hmWanMbusA5Value1D		OBJECT-TYPE
			SYNTAX	INTEGER
			MAX-ACCESS	read-only
			STATUS	current
			::= { hmWanMbusA5 65 }

hmWanMbusA5VIF1E		OBJECT-TYPE
			SYNTAX	INTEGER
			MAX-ACCESS	read-only
			STATUS	current
			::= { hmWanMbusA5 66 }

hmWanMbusA5Value1E		OBJECT-TYPE
			SYNTAX	INTEGER
			MAX-ACCESS	read-only
			STATUS	current
			::= { hmWanMbusA5 67 }

hmWanMbusA5VIF1F		OBJECT-TYPE
			SYNTAX	INTEGER
			MAX-ACCESS	read-only
			STATUS	current
			::= { hmWanMbusA5 68 }

hmWanMbusA5Value1F		OBJECT-TYPE
			SYNTAX	INTEGER
			MAX-ACCESS	read-only
			STATUS	current
			::= { hmWanMbusA5 69 }

hmWanMbusA5VIF20		OBJECT-TYPE
			SYNTAX	INTEGER
			MAX-ACCESS	read-only
			STATUS	current
			::= { hmWanMbusA5 70 }

hmWanMbusA5Value20		OBJECT-TYPE
			SYNTAX	INTEGER
			MAX-ACCESS	read-only
			STATUS	current
			::= { hmWanMbusA5 71 }

hmWanMbusA5VIF21		OBJECT-TYPE
			SYNTAX	INTEGER
			MAX-ACCESS	read-only
			STATUS	current
			::= { hmWanMbusA5 72 }

hmWanMbusA5Value21		OBJECT-TYPE
			SYNTAX	INTEGER
			MAX-ACCESS	read-only
			STATUS	current
			::= { hmWanMbusA5 73 }

hmWanMbusA5VIF22		OBJECT-TYPE
			SYNTAX	INTEGER
			MAX-ACCESS	read-only
			STATUS	current
			::= { hmWanMbusA5 74 }

hmWanMbusA5Value22		OBJECT-TYPE
			SYNTAX	INTEGER
			MAX-ACCESS	read-only
			STATUS	current
			::= { hmWanMbusA5 75 }

hmWanMbusA5VIF23		OBJECT-TYPE
			SYNTAX	INTEGER
			MAX-ACCESS	read-only
			STATUS	current
			::= { hmWanMbusA5 76 }

hmWanMbusA5Value23		OBJECT-TYPE
			SYNTAX	INTEGER
			MAX-ACCESS	read-only
			STATUS	current
			::= { hmWanMbusA5 77 }

hmWanMbusA5VIF24		OBJECT-TYPE
			SYNTAX	INTEGER
			MAX-ACCESS	read-only
			STATUS	current
			::= { hmWanMbusA5 78 }

hmWanMbusA5Value24		OBJECT-TYPE
			SYNTAX	INTEGER
			MAX-ACCESS	read-only
			STATUS	current
			::= { hmWanMbusA5 79 }

hmWanMbusA5VIF25		OBJECT-TYPE
			SYNTAX	INTEGER
			MAX-ACCESS	read-only
			STATUS	current
			::= { hmWanMbusA5 80 }

hmWanMbusA5Value25		OBJECT-TYPE
			SYNTAX	INTEGER
			MAX-ACCESS	read-only
			STATUS	current
			::= { hmWanMbusA5 81 }

hmWanMbusA5VIF26		OBJECT-TYPE
			SYNTAX	INTEGER
			MAX-ACCESS	read-only
			STATUS	current
			::= { hmWanMbusA5 82 }

hmWanMbusA5Value26		OBJECT-TYPE
			SYNTAX	INTEGER
			MAX-ACCESS	read-only
			STATUS	current
			::= { hmWanMbusA5 83 }

hmWanMbusA5VIF27		OBJECT-TYPE
			SYNTAX	INTEGER
			MAX-ACCESS	read-only
			STATUS	current
			::= { hmWanMbusA5 84 }

hmWanMbusA5Value27		OBJECT-TYPE
			SYNTAX	INTEGER
			MAX-ACCESS	read-only
			STATUS	current
			::= { hmWanMbusA5 85 }

hmWanMbusA5VIF28		OBJECT-TYPE
			SYNTAX	INTEGER
			MAX-ACCESS	read-only
			STATUS	current
			::= { hmWanMbusA5 86 }

hmWanMbusA5Value28		OBJECT-TYPE
			SYNTAX	INTEGER
			MAX-ACCESS	read-only
			STATUS	current
			::= { hmWanMbusA5 87 }

hmWanMbusA5VIF29		OBJECT-TYPE
			SYNTAX	INTEGER
			MAX-ACCESS	read-only
			STATUS	current
			::= { hmWanMbusA5 88 }

hmWanMbusA5Value29		OBJECT-TYPE
			SYNTAX	INTEGER
			MAX-ACCESS	read-only
			STATUS	current
			::= { hmWanMbusA5 89 }

hmWanMbusA5VIF2A		OBJECT-TYPE
			SYNTAX	INTEGER
			MAX-ACCESS	read-only
			STATUS	current
			::= { hmWanMbusA5 90 }

hmWanMbusA5Value2A		OBJECT-TYPE
			SYNTAX	INTEGER
			MAX-ACCESS	read-only
			STATUS	current
			::= { hmWanMbusA5 91 }

hmWanMbusA5VIF2B		OBJECT-TYPE
			SYNTAX	INTEGER
			MAX-ACCESS	read-only
			STATUS	current
			::= { hmWanMbusA5 92 }

hmWanMbusA5Value2B		OBJECT-TYPE
			SYNTAX	INTEGER
			MAX-ACCESS	read-only
			STATUS	current
			::= { hmWanMbusA5 93 }

hmWanMbusA5VIF2C		OBJECT-TYPE
			SYNTAX	INTEGER
			MAX-ACCESS	read-only
			STATUS	current
			::= { hmWanMbusA5 94 }

hmWanMbusA5Value2C		OBJECT-TYPE
			SYNTAX	INTEGER
			MAX-ACCESS	read-only
			STATUS	current
			::= { hmWanMbusA5 95 }

hmWanMbusA5VIF2D		OBJECT-TYPE
			SYNTAX	INTEGER
			MAX-ACCESS	read-only
			STATUS	current
			::= { hmWanMbusA5 96 }

hmWanMbusA5Value2D		OBJECT-TYPE
			SYNTAX	INTEGER
			MAX-ACCESS	read-only
			STATUS	current
			::= { hmWanMbusA5 97 }

hmWanMbusA5VIF2E		OBJECT-TYPE
			SYNTAX	INTEGER
			MAX-ACCESS	read-only
			STATUS	current
			::= { hmWanMbusA5 98 }

hmWanMbusA5Value2E		OBJECT-TYPE
			SYNTAX	INTEGER
			MAX-ACCESS	read-only
			STATUS	current
			::= { hmWanMbusA5 99 }

hmWanMbusA5VIF2F		OBJECT-TYPE
			SYNTAX	INTEGER
			MAX-ACCESS	read-only
			STATUS	current
			::= { hmWanMbusA5 100 }

hmWanMbusA5Value2F		OBJECT-TYPE
			SYNTAX	INTEGER
			MAX-ACCESS	read-only
			STATUS	current
			::= { hmWanMbusA5 101 }

hmWanMbusA6			OBJECT IDENTIFIER ::= { hmWanMbus 166 }

hmWanMbusA6IdNumber		OBJECT-TYPE
			SYNTAX	Gauge32
			MAX-ACCESS	read-only
			STATUS	current
			::= { hmWanMbusA6 1 }

hmWanMbusA6Manufacturer	OBJECT-TYPE
			SYNTAX	Gauge32
			MAX-ACCESS	read-only
			STATUS	current
			::= { hmWanMbusA6 2 }

hmWanMbusA6Version		OBJECT-TYPE
			SYNTAX	Gauge32
			MAX-ACCESS	read-only
			STATUS	current
			::= { hmWanMbusA6 3 }

hmWanMbusA6Medium		OBJECT-TYPE
			SYNTAX	Gauge32
			MAX-ACCESS	read-only
			STATUS	current
			::= { hmWanMbusA6 4 }

hmWanMbusA6Status		OBJECT-TYPE
			SYNTAX	Gauge32
			MAX-ACCESS	read-only
			STATUS	current
			::= { hmWanMbusA6 5 }

hmWanMbusA6VIF00		OBJECT-TYPE
			SYNTAX	INTEGER
			MAX-ACCESS	read-only
			STATUS	current
			::= { hmWanMbusA6 6 }

hmWanMbusA6Value00		OBJECT-TYPE
			SYNTAX	INTEGER
			MAX-ACCESS	read-only
			STATUS	current
			::= { hmWanMbusA6 7 }

hmWanMbusA6VIF01		OBJECT-TYPE
			SYNTAX	INTEGER
			MAX-ACCESS	read-only
			STATUS	current
			::= { hmWanMbusA6 8 }

hmWanMbusA6Value01		OBJECT-TYPE
			SYNTAX	INTEGER
			MAX-ACCESS	read-only
			STATUS	current
			::= { hmWanMbusA6 9 }

hmWanMbusA6VIF02		OBJECT-TYPE
			SYNTAX	INTEGER
			MAX-ACCESS	read-only
			STATUS	current
			::= { hmWanMbusA6 10 }

hmWanMbusA6Value02		OBJECT-TYPE
			SYNTAX	INTEGER
			MAX-ACCESS	read-only
			STATUS	current
			::= { hmWanMbusA6 11 }

hmWanMbusA6VIF03		OBJECT-TYPE
			SYNTAX	INTEGER
			MAX-ACCESS	read-only
			STATUS	current
			::= { hmWanMbusA6 12 }

hmWanMbusA6Value03		OBJECT-TYPE
			SYNTAX	INTEGER
			MAX-ACCESS	read-only
			STATUS	current
			::= { hmWanMbusA6 13 }

hmWanMbusA6VIF04		OBJECT-TYPE
			SYNTAX	INTEGER
			MAX-ACCESS	read-only
			STATUS	current
			::= { hmWanMbusA6 14 }

hmWanMbusA6Value04		OBJECT-TYPE
			SYNTAX	INTEGER
			MAX-ACCESS	read-only
			STATUS	current
			::= { hmWanMbusA6 15 }

hmWanMbusA6VIF05		OBJECT-TYPE
			SYNTAX	INTEGER
			MAX-ACCESS	read-only
			STATUS	current
			::= { hmWanMbusA6 16 }

hmWanMbusA6Value05		OBJECT-TYPE
			SYNTAX	INTEGER
			MAX-ACCESS	read-only
			STATUS	current
			::= { hmWanMbusA6 17 }

hmWanMbusA6VIF06		OBJECT-TYPE
			SYNTAX	INTEGER
			MAX-ACCESS	read-only
			STATUS	current
			::= { hmWanMbusA6 18 }

hmWanMbusA6Value06		OBJECT-TYPE
			SYNTAX	INTEGER
			MAX-ACCESS	read-only
			STATUS	current
			::= { hmWanMbusA6 19 }

hmWanMbusA6VIF07		OBJECT-TYPE
			SYNTAX	INTEGER
			MAX-ACCESS	read-only
			STATUS	current
			::= { hmWanMbusA6 20 }

hmWanMbusA6Value07		OBJECT-TYPE
			SYNTAX	INTEGER
			MAX-ACCESS	read-only
			STATUS	current
			::= { hmWanMbusA6 21 }

hmWanMbusA6VIF08		OBJECT-TYPE
			SYNTAX	INTEGER
			MAX-ACCESS	read-only
			STATUS	current
			::= { hmWanMbusA6 22 }

hmWanMbusA6Value08		OBJECT-TYPE
			SYNTAX	INTEGER
			MAX-ACCESS	read-only
			STATUS	current
			::= { hmWanMbusA6 23 }

hmWanMbusA6VIF09		OBJECT-TYPE
			SYNTAX	INTEGER
			MAX-ACCESS	read-only
			STATUS	current
			::= { hmWanMbusA6 24 }

hmWanMbusA6Value09		OBJECT-TYPE
			SYNTAX	INTEGER
			MAX-ACCESS	read-only
			STATUS	current
			::= { hmWanMbusA6 25 }

hmWanMbusA6VIF0A		OBJECT-TYPE
			SYNTAX	INTEGER
			MAX-ACCESS	read-only
			STATUS	current
			::= { hmWanMbusA6 26 }

hmWanMbusA6Value0A		OBJECT-TYPE
			SYNTAX	INTEGER
			MAX-ACCESS	read-only
			STATUS	current
			::= { hmWanMbusA6 27 }

hmWanMbusA6VIF0B		OBJECT-TYPE
			SYNTAX	INTEGER
			MAX-ACCESS	read-only
			STATUS	current
			::= { hmWanMbusA6 28 }

hmWanMbusA6Value0B		OBJECT-TYPE
			SYNTAX	INTEGER
			MAX-ACCESS	read-only
			STATUS	current
			::= { hmWanMbusA6 29 }

hmWanMbusA6VIF0C		OBJECT-TYPE
			SYNTAX	INTEGER
			MAX-ACCESS	read-only
			STATUS	current
			::= { hmWanMbusA6 30 }

hmWanMbusA6Value0C		OBJECT-TYPE
			SYNTAX	INTEGER
			MAX-ACCESS	read-only
			STATUS	current
			::= { hmWanMbusA6 31 }

hmWanMbusA6VIF0D		OBJECT-TYPE
			SYNTAX	INTEGER
			MAX-ACCESS	read-only
			STATUS	current
			::= { hmWanMbusA6 32 }

hmWanMbusA6Value0D		OBJECT-TYPE
			SYNTAX	INTEGER
			MAX-ACCESS	read-only
			STATUS	current
			::= { hmWanMbusA6 33 }

hmWanMbusA6VIF0E		OBJECT-TYPE
			SYNTAX	INTEGER
			MAX-ACCESS	read-only
			STATUS	current
			::= { hmWanMbusA6 34 }

hmWanMbusA6Value0E		OBJECT-TYPE
			SYNTAX	INTEGER
			MAX-ACCESS	read-only
			STATUS	current
			::= { hmWanMbusA6 35 }

hmWanMbusA6VIF0F		OBJECT-TYPE
			SYNTAX	INTEGER
			MAX-ACCESS	read-only
			STATUS	current
			::= { hmWanMbusA6 36 }

hmWanMbusA6Value0F		OBJECT-TYPE
			SYNTAX	INTEGER
			MAX-ACCESS	read-only
			STATUS	current
			::= { hmWanMbusA6 37 }

hmWanMbusA6VIF10		OBJECT-TYPE
			SYNTAX	INTEGER
			MAX-ACCESS	read-only
			STATUS	current
			::= { hmWanMbusA6 38 }

hmWanMbusA6Value10		OBJECT-TYPE
			SYNTAX	INTEGER
			MAX-ACCESS	read-only
			STATUS	current
			::= { hmWanMbusA6 39 }

hmWanMbusA6VIF11		OBJECT-TYPE
			SYNTAX	INTEGER
			MAX-ACCESS	read-only
			STATUS	current
			::= { hmWanMbusA6 40 }

hmWanMbusA6Value11		OBJECT-TYPE
			SYNTAX	INTEGER
			MAX-ACCESS	read-only
			STATUS	current
			::= { hmWanMbusA6 41 }

hmWanMbusA6VIF12		OBJECT-TYPE
			SYNTAX	INTEGER
			MAX-ACCESS	read-only
			STATUS	current
			::= { hmWanMbusA6 42 }

hmWanMbusA6Value12		OBJECT-TYPE
			SYNTAX	INTEGER
			MAX-ACCESS	read-only
			STATUS	current
			::= { hmWanMbusA6 43 }

hmWanMbusA6VIF13		OBJECT-TYPE
			SYNTAX	INTEGER
			MAX-ACCESS	read-only
			STATUS	current
			::= { hmWanMbusA6 44 }

hmWanMbusA6Value13		OBJECT-TYPE
			SYNTAX	INTEGER
			MAX-ACCESS	read-only
			STATUS	current
			::= { hmWanMbusA6 45 }

hmWanMbusA6VIF14		OBJECT-TYPE
			SYNTAX	INTEGER
			MAX-ACCESS	read-only
			STATUS	current
			::= { hmWanMbusA6 46 }

hmWanMbusA6Value14		OBJECT-TYPE
			SYNTAX	INTEGER
			MAX-ACCESS	read-only
			STATUS	current
			::= { hmWanMbusA6 47 }

hmWanMbusA6VIF15		OBJECT-TYPE
			SYNTAX	INTEGER
			MAX-ACCESS	read-only
			STATUS	current
			::= { hmWanMbusA6 48 }

hmWanMbusA6Value15		OBJECT-TYPE
			SYNTAX	INTEGER
			MAX-ACCESS	read-only
			STATUS	current
			::= { hmWanMbusA6 49 }

hmWanMbusA6VIF16		OBJECT-TYPE
			SYNTAX	INTEGER
			MAX-ACCESS	read-only
			STATUS	current
			::= { hmWanMbusA6 50 }

hmWanMbusA6Value16		OBJECT-TYPE
			SYNTAX	INTEGER
			MAX-ACCESS	read-only
			STATUS	current
			::= { hmWanMbusA6 51 }

hmWanMbusA6VIF17		OBJECT-TYPE
			SYNTAX	INTEGER
			MAX-ACCESS	read-only
			STATUS	current
			::= { hmWanMbusA6 52 }

hmWanMbusA6Value17		OBJECT-TYPE
			SYNTAX	INTEGER
			MAX-ACCESS	read-only
			STATUS	current
			::= { hmWanMbusA6 53 }

hmWanMbusA6VIF18		OBJECT-TYPE
			SYNTAX	INTEGER
			MAX-ACCESS	read-only
			STATUS	current
			::= { hmWanMbusA6 54 }

hmWanMbusA6Value18		OBJECT-TYPE
			SYNTAX	INTEGER
			MAX-ACCESS	read-only
			STATUS	current
			::= { hmWanMbusA6 55 }

hmWanMbusA6VIF19		OBJECT-TYPE
			SYNTAX	INTEGER
			MAX-ACCESS	read-only
			STATUS	current
			::= { hmWanMbusA6 56 }

hmWanMbusA6Value19		OBJECT-TYPE
			SYNTAX	INTEGER
			MAX-ACCESS	read-only
			STATUS	current
			::= { hmWanMbusA6 57 }

hmWanMbusA6VIF1A		OBJECT-TYPE
			SYNTAX	INTEGER
			MAX-ACCESS	read-only
			STATUS	current
			::= { hmWanMbusA6 58 }

hmWanMbusA6Value1A		OBJECT-TYPE
			SYNTAX	INTEGER
			MAX-ACCESS	read-only
			STATUS	current
			::= { hmWanMbusA6 59 }

hmWanMbusA6VIF1B		OBJECT-TYPE
			SYNTAX	INTEGER
			MAX-ACCESS	read-only
			STATUS	current
			::= { hmWanMbusA6 60 }

hmWanMbusA6Value1B		OBJECT-TYPE
			SYNTAX	INTEGER
			MAX-ACCESS	read-only
			STATUS	current
			::= { hmWanMbusA6 61 }

hmWanMbusA6VIF1C		OBJECT-TYPE
			SYNTAX	INTEGER
			MAX-ACCESS	read-only
			STATUS	current
			::= { hmWanMbusA6 62 }

hmWanMbusA6Value1C		OBJECT-TYPE
			SYNTAX	INTEGER
			MAX-ACCESS	read-only
			STATUS	current
			::= { hmWanMbusA6 63 }

hmWanMbusA6VIF1D		OBJECT-TYPE
			SYNTAX	INTEGER
			MAX-ACCESS	read-only
			STATUS	current
			::= { hmWanMbusA6 64 }

hmWanMbusA6Value1D		OBJECT-TYPE
			SYNTAX	INTEGER
			MAX-ACCESS	read-only
			STATUS	current
			::= { hmWanMbusA6 65 }

hmWanMbusA6VIF1E		OBJECT-TYPE
			SYNTAX	INTEGER
			MAX-ACCESS	read-only
			STATUS	current
			::= { hmWanMbusA6 66 }

hmWanMbusA6Value1E		OBJECT-TYPE
			SYNTAX	INTEGER
			MAX-ACCESS	read-only
			STATUS	current
			::= { hmWanMbusA6 67 }

hmWanMbusA6VIF1F		OBJECT-TYPE
			SYNTAX	INTEGER
			MAX-ACCESS	read-only
			STATUS	current
			::= { hmWanMbusA6 68 }

hmWanMbusA6Value1F		OBJECT-TYPE
			SYNTAX	INTEGER
			MAX-ACCESS	read-only
			STATUS	current
			::= { hmWanMbusA6 69 }

hmWanMbusA6VIF20		OBJECT-TYPE
			SYNTAX	INTEGER
			MAX-ACCESS	read-only
			STATUS	current
			::= { hmWanMbusA6 70 }

hmWanMbusA6Value20		OBJECT-TYPE
			SYNTAX	INTEGER
			MAX-ACCESS	read-only
			STATUS	current
			::= { hmWanMbusA6 71 }

hmWanMbusA6VIF21		OBJECT-TYPE
			SYNTAX	INTEGER
			MAX-ACCESS	read-only
			STATUS	current
			::= { hmWanMbusA6 72 }

hmWanMbusA6Value21		OBJECT-TYPE
			SYNTAX	INTEGER
			MAX-ACCESS	read-only
			STATUS	current
			::= { hmWanMbusA6 73 }

hmWanMbusA6VIF22		OBJECT-TYPE
			SYNTAX	INTEGER
			MAX-ACCESS	read-only
			STATUS	current
			::= { hmWanMbusA6 74 }

hmWanMbusA6Value22		OBJECT-TYPE
			SYNTAX	INTEGER
			MAX-ACCESS	read-only
			STATUS	current
			::= { hmWanMbusA6 75 }

hmWanMbusA6VIF23		OBJECT-TYPE
			SYNTAX	INTEGER
			MAX-ACCESS	read-only
			STATUS	current
			::= { hmWanMbusA6 76 }

hmWanMbusA6Value23		OBJECT-TYPE
			SYNTAX	INTEGER
			MAX-ACCESS	read-only
			STATUS	current
			::= { hmWanMbusA6 77 }

hmWanMbusA6VIF24		OBJECT-TYPE
			SYNTAX	INTEGER
			MAX-ACCESS	read-only
			STATUS	current
			::= { hmWanMbusA6 78 }

hmWanMbusA6Value24		OBJECT-TYPE
			SYNTAX	INTEGER
			MAX-ACCESS	read-only
			STATUS	current
			::= { hmWanMbusA6 79 }

hmWanMbusA6VIF25		OBJECT-TYPE
			SYNTAX	INTEGER
			MAX-ACCESS	read-only
			STATUS	current
			::= { hmWanMbusA6 80 }

hmWanMbusA6Value25		OBJECT-TYPE
			SYNTAX	INTEGER
			MAX-ACCESS	read-only
			STATUS	current
			::= { hmWanMbusA6 81 }

hmWanMbusA6VIF26		OBJECT-TYPE
			SYNTAX	INTEGER
			MAX-ACCESS	read-only
			STATUS	current
			::= { hmWanMbusA6 82 }

hmWanMbusA6Value26		OBJECT-TYPE
			SYNTAX	INTEGER
			MAX-ACCESS	read-only
			STATUS	current
			::= { hmWanMbusA6 83 }

hmWanMbusA6VIF27		OBJECT-TYPE
			SYNTAX	INTEGER
			MAX-ACCESS	read-only
			STATUS	current
			::= { hmWanMbusA6 84 }

hmWanMbusA6Value27		OBJECT-TYPE
			SYNTAX	INTEGER
			MAX-ACCESS	read-only
			STATUS	current
			::= { hmWanMbusA6 85 }

hmWanMbusA6VIF28		OBJECT-TYPE
			SYNTAX	INTEGER
			MAX-ACCESS	read-only
			STATUS	current
			::= { hmWanMbusA6 86 }

hmWanMbusA6Value28		OBJECT-TYPE
			SYNTAX	INTEGER
			MAX-ACCESS	read-only
			STATUS	current
			::= { hmWanMbusA6 87 }

hmWanMbusA6VIF29		OBJECT-TYPE
			SYNTAX	INTEGER
			MAX-ACCESS	read-only
			STATUS	current
			::= { hmWanMbusA6 88 }

hmWanMbusA6Value29		OBJECT-TYPE
			SYNTAX	INTEGER
			MAX-ACCESS	read-only
			STATUS	current
			::= { hmWanMbusA6 89 }

hmWanMbusA6VIF2A		OBJECT-TYPE
			SYNTAX	INTEGER
			MAX-ACCESS	read-only
			STATUS	current
			::= { hmWanMbusA6 90 }

hmWanMbusA6Value2A		OBJECT-TYPE
			SYNTAX	INTEGER
			MAX-ACCESS	read-only
			STATUS	current
			::= { hmWanMbusA6 91 }

hmWanMbusA6VIF2B		OBJECT-TYPE
			SYNTAX	INTEGER
			MAX-ACCESS	read-only
			STATUS	current
			::= { hmWanMbusA6 92 }

hmWanMbusA6Value2B		OBJECT-TYPE
			SYNTAX	INTEGER
			MAX-ACCESS	read-only
			STATUS	current
			::= { hmWanMbusA6 93 }

hmWanMbusA6VIF2C		OBJECT-TYPE
			SYNTAX	INTEGER
			MAX-ACCESS	read-only
			STATUS	current
			::= { hmWanMbusA6 94 }

hmWanMbusA6Value2C		OBJECT-TYPE
			SYNTAX	INTEGER
			MAX-ACCESS	read-only
			STATUS	current
			::= { hmWanMbusA6 95 }

hmWanMbusA6VIF2D		OBJECT-TYPE
			SYNTAX	INTEGER
			MAX-ACCESS	read-only
			STATUS	current
			::= { hmWanMbusA6 96 }

hmWanMbusA6Value2D		OBJECT-TYPE
			SYNTAX	INTEGER
			MAX-ACCESS	read-only
			STATUS	current
			::= { hmWanMbusA6 97 }

hmWanMbusA6VIF2E		OBJECT-TYPE
			SYNTAX	INTEGER
			MAX-ACCESS	read-only
			STATUS	current
			::= { hmWanMbusA6 98 }

hmWanMbusA6Value2E		OBJECT-TYPE
			SYNTAX	INTEGER
			MAX-ACCESS	read-only
			STATUS	current
			::= { hmWanMbusA6 99 }

hmWanMbusA6VIF2F		OBJECT-TYPE
			SYNTAX	INTEGER
			MAX-ACCESS	read-only
			STATUS	current
			::= { hmWanMbusA6 100 }

hmWanMbusA6Value2F		OBJECT-TYPE
			SYNTAX	INTEGER
			MAX-ACCESS	read-only
			STATUS	current
			::= { hmWanMbusA6 101 }

hmWanMbusA7			OBJECT IDENTIFIER ::= { hmWanMbus 167 }

hmWanMbusA7IdNumber		OBJECT-TYPE
			SYNTAX	Gauge32
			MAX-ACCESS	read-only
			STATUS	current
			::= { hmWanMbusA7 1 }

hmWanMbusA7Manufacturer	OBJECT-TYPE
			SYNTAX	Gauge32
			MAX-ACCESS	read-only
			STATUS	current
			::= { hmWanMbusA7 2 }

hmWanMbusA7Version		OBJECT-TYPE
			SYNTAX	Gauge32
			MAX-ACCESS	read-only
			STATUS	current
			::= { hmWanMbusA7 3 }

hmWanMbusA7Medium		OBJECT-TYPE
			SYNTAX	Gauge32
			MAX-ACCESS	read-only
			STATUS	current
			::= { hmWanMbusA7 4 }

hmWanMbusA7Status		OBJECT-TYPE
			SYNTAX	Gauge32
			MAX-ACCESS	read-only
			STATUS	current
			::= { hmWanMbusA7 5 }

hmWanMbusA7VIF00		OBJECT-TYPE
			SYNTAX	INTEGER
			MAX-ACCESS	read-only
			STATUS	current
			::= { hmWanMbusA7 6 }

hmWanMbusA7Value00		OBJECT-TYPE
			SYNTAX	INTEGER
			MAX-ACCESS	read-only
			STATUS	current
			::= { hmWanMbusA7 7 }

hmWanMbusA7VIF01		OBJECT-TYPE
			SYNTAX	INTEGER
			MAX-ACCESS	read-only
			STATUS	current
			::= { hmWanMbusA7 8 }

hmWanMbusA7Value01		OBJECT-TYPE
			SYNTAX	INTEGER
			MAX-ACCESS	read-only
			STATUS	current
			::= { hmWanMbusA7 9 }

hmWanMbusA7VIF02		OBJECT-TYPE
			SYNTAX	INTEGER
			MAX-ACCESS	read-only
			STATUS	current
			::= { hmWanMbusA7 10 }

hmWanMbusA7Value02		OBJECT-TYPE
			SYNTAX	INTEGER
			MAX-ACCESS	read-only
			STATUS	current
			::= { hmWanMbusA7 11 }

hmWanMbusA7VIF03		OBJECT-TYPE
			SYNTAX	INTEGER
			MAX-ACCESS	read-only
			STATUS	current
			::= { hmWanMbusA7 12 }

hmWanMbusA7Value03		OBJECT-TYPE
			SYNTAX	INTEGER
			MAX-ACCESS	read-only
			STATUS	current
			::= { hmWanMbusA7 13 }

hmWanMbusA7VIF04		OBJECT-TYPE
			SYNTAX	INTEGER
			MAX-ACCESS	read-only
			STATUS	current
			::= { hmWanMbusA7 14 }

hmWanMbusA7Value04		OBJECT-TYPE
			SYNTAX	INTEGER
			MAX-ACCESS	read-only
			STATUS	current
			::= { hmWanMbusA7 15 }

hmWanMbusA7VIF05		OBJECT-TYPE
			SYNTAX	INTEGER
			MAX-ACCESS	read-only
			STATUS	current
			::= { hmWanMbusA7 16 }

hmWanMbusA7Value05		OBJECT-TYPE
			SYNTAX	INTEGER
			MAX-ACCESS	read-only
			STATUS	current
			::= { hmWanMbusA7 17 }

hmWanMbusA7VIF06		OBJECT-TYPE
			SYNTAX	INTEGER
			MAX-ACCESS	read-only
			STATUS	current
			::= { hmWanMbusA7 18 }

hmWanMbusA7Value06		OBJECT-TYPE
			SYNTAX	INTEGER
			MAX-ACCESS	read-only
			STATUS	current
			::= { hmWanMbusA7 19 }

hmWanMbusA7VIF07		OBJECT-TYPE
			SYNTAX	INTEGER
			MAX-ACCESS	read-only
			STATUS	current
			::= { hmWanMbusA7 20 }

hmWanMbusA7Value07		OBJECT-TYPE
			SYNTAX	INTEGER
			MAX-ACCESS	read-only
			STATUS	current
			::= { hmWanMbusA7 21 }

hmWanMbusA7VIF08		OBJECT-TYPE
			SYNTAX	INTEGER
			MAX-ACCESS	read-only
			STATUS	current
			::= { hmWanMbusA7 22 }

hmWanMbusA7Value08		OBJECT-TYPE
			SYNTAX	INTEGER
			MAX-ACCESS	read-only
			STATUS	current
			::= { hmWanMbusA7 23 }

hmWanMbusA7VIF09		OBJECT-TYPE
			SYNTAX	INTEGER
			MAX-ACCESS	read-only
			STATUS	current
			::= { hmWanMbusA7 24 }

hmWanMbusA7Value09		OBJECT-TYPE
			SYNTAX	INTEGER
			MAX-ACCESS	read-only
			STATUS	current
			::= { hmWanMbusA7 25 }

hmWanMbusA7VIF0A		OBJECT-TYPE
			SYNTAX	INTEGER
			MAX-ACCESS	read-only
			STATUS	current
			::= { hmWanMbusA7 26 }

hmWanMbusA7Value0A		OBJECT-TYPE
			SYNTAX	INTEGER
			MAX-ACCESS	read-only
			STATUS	current
			::= { hmWanMbusA7 27 }

hmWanMbusA7VIF0B		OBJECT-TYPE
			SYNTAX	INTEGER
			MAX-ACCESS	read-only
			STATUS	current
			::= { hmWanMbusA7 28 }

hmWanMbusA7Value0B		OBJECT-TYPE
			SYNTAX	INTEGER
			MAX-ACCESS	read-only
			STATUS	current
			::= { hmWanMbusA7 29 }

hmWanMbusA7VIF0C		OBJECT-TYPE
			SYNTAX	INTEGER
			MAX-ACCESS	read-only
			STATUS	current
			::= { hmWanMbusA7 30 }

hmWanMbusA7Value0C		OBJECT-TYPE
			SYNTAX	INTEGER
			MAX-ACCESS	read-only
			STATUS	current
			::= { hmWanMbusA7 31 }

hmWanMbusA7VIF0D		OBJECT-TYPE
			SYNTAX	INTEGER
			MAX-ACCESS	read-only
			STATUS	current
			::= { hmWanMbusA7 32 }

hmWanMbusA7Value0D		OBJECT-TYPE
			SYNTAX	INTEGER
			MAX-ACCESS	read-only
			STATUS	current
			::= { hmWanMbusA7 33 }

hmWanMbusA7VIF0E		OBJECT-TYPE
			SYNTAX	INTEGER
			MAX-ACCESS	read-only
			STATUS	current
			::= { hmWanMbusA7 34 }

hmWanMbusA7Value0E		OBJECT-TYPE
			SYNTAX	INTEGER
			MAX-ACCESS	read-only
			STATUS	current
			::= { hmWanMbusA7 35 }

hmWanMbusA7VIF0F		OBJECT-TYPE
			SYNTAX	INTEGER
			MAX-ACCESS	read-only
			STATUS	current
			::= { hmWanMbusA7 36 }

hmWanMbusA7Value0F		OBJECT-TYPE
			SYNTAX	INTEGER
			MAX-ACCESS	read-only
			STATUS	current
			::= { hmWanMbusA7 37 }

hmWanMbusA7VIF10		OBJECT-TYPE
			SYNTAX	INTEGER
			MAX-ACCESS	read-only
			STATUS	current
			::= { hmWanMbusA7 38 }

hmWanMbusA7Value10		OBJECT-TYPE
			SYNTAX	INTEGER
			MAX-ACCESS	read-only
			STATUS	current
			::= { hmWanMbusA7 39 }

hmWanMbusA7VIF11		OBJECT-TYPE
			SYNTAX	INTEGER
			MAX-ACCESS	read-only
			STATUS	current
			::= { hmWanMbusA7 40 }

hmWanMbusA7Value11		OBJECT-TYPE
			SYNTAX	INTEGER
			MAX-ACCESS	read-only
			STATUS	current
			::= { hmWanMbusA7 41 }

hmWanMbusA7VIF12		OBJECT-TYPE
			SYNTAX	INTEGER
			MAX-ACCESS	read-only
			STATUS	current
			::= { hmWanMbusA7 42 }

hmWanMbusA7Value12		OBJECT-TYPE
			SYNTAX	INTEGER
			MAX-ACCESS	read-only
			STATUS	current
			::= { hmWanMbusA7 43 }

hmWanMbusA7VIF13		OBJECT-TYPE
			SYNTAX	INTEGER
			MAX-ACCESS	read-only
			STATUS	current
			::= { hmWanMbusA7 44 }

hmWanMbusA7Value13		OBJECT-TYPE
			SYNTAX	INTEGER
			MAX-ACCESS	read-only
			STATUS	current
			::= { hmWanMbusA7 45 }

hmWanMbusA7VIF14		OBJECT-TYPE
			SYNTAX	INTEGER
			MAX-ACCESS	read-only
			STATUS	current
			::= { hmWanMbusA7 46 }

hmWanMbusA7Value14		OBJECT-TYPE
			SYNTAX	INTEGER
			MAX-ACCESS	read-only
			STATUS	current
			::= { hmWanMbusA7 47 }

hmWanMbusA7VIF15		OBJECT-TYPE
			SYNTAX	INTEGER
			MAX-ACCESS	read-only
			STATUS	current
			::= { hmWanMbusA7 48 }

hmWanMbusA7Value15		OBJECT-TYPE
			SYNTAX	INTEGER
			MAX-ACCESS	read-only
			STATUS	current
			::= { hmWanMbusA7 49 }

hmWanMbusA7VIF16		OBJECT-TYPE
			SYNTAX	INTEGER
			MAX-ACCESS	read-only
			STATUS	current
			::= { hmWanMbusA7 50 }

hmWanMbusA7Value16		OBJECT-TYPE
			SYNTAX	INTEGER
			MAX-ACCESS	read-only
			STATUS	current
			::= { hmWanMbusA7 51 }

hmWanMbusA7VIF17		OBJECT-TYPE
			SYNTAX	INTEGER
			MAX-ACCESS	read-only
			STATUS	current
			::= { hmWanMbusA7 52 }

hmWanMbusA7Value17		OBJECT-TYPE
			SYNTAX	INTEGER
			MAX-ACCESS	read-only
			STATUS	current
			::= { hmWanMbusA7 53 }

hmWanMbusA7VIF18		OBJECT-TYPE
			SYNTAX	INTEGER
			MAX-ACCESS	read-only
			STATUS	current
			::= { hmWanMbusA7 54 }

hmWanMbusA7Value18		OBJECT-TYPE
			SYNTAX	INTEGER
			MAX-ACCESS	read-only
			STATUS	current
			::= { hmWanMbusA7 55 }

hmWanMbusA7VIF19		OBJECT-TYPE
			SYNTAX	INTEGER
			MAX-ACCESS	read-only
			STATUS	current
			::= { hmWanMbusA7 56 }

hmWanMbusA7Value19		OBJECT-TYPE
			SYNTAX	INTEGER
			MAX-ACCESS	read-only
			STATUS	current
			::= { hmWanMbusA7 57 }

hmWanMbusA7VIF1A		OBJECT-TYPE
			SYNTAX	INTEGER
			MAX-ACCESS	read-only
			STATUS	current
			::= { hmWanMbusA7 58 }

hmWanMbusA7Value1A		OBJECT-TYPE
			SYNTAX	INTEGER
			MAX-ACCESS	read-only
			STATUS	current
			::= { hmWanMbusA7 59 }

hmWanMbusA7VIF1B		OBJECT-TYPE
			SYNTAX	INTEGER
			MAX-ACCESS	read-only
			STATUS	current
			::= { hmWanMbusA7 60 }

hmWanMbusA7Value1B		OBJECT-TYPE
			SYNTAX	INTEGER
			MAX-ACCESS	read-only
			STATUS	current
			::= { hmWanMbusA7 61 }

hmWanMbusA7VIF1C		OBJECT-TYPE
			SYNTAX	INTEGER
			MAX-ACCESS	read-only
			STATUS	current
			::= { hmWanMbusA7 62 }

hmWanMbusA7Value1C		OBJECT-TYPE
			SYNTAX	INTEGER
			MAX-ACCESS	read-only
			STATUS	current
			::= { hmWanMbusA7 63 }

hmWanMbusA7VIF1D		OBJECT-TYPE
			SYNTAX	INTEGER
			MAX-ACCESS	read-only
			STATUS	current
			::= { hmWanMbusA7 64 }

hmWanMbusA7Value1D		OBJECT-TYPE
			SYNTAX	INTEGER
			MAX-ACCESS	read-only
			STATUS	current
			::= { hmWanMbusA7 65 }

hmWanMbusA7VIF1E		OBJECT-TYPE
			SYNTAX	INTEGER
			MAX-ACCESS	read-only
			STATUS	current
			::= { hmWanMbusA7 66 }

hmWanMbusA7Value1E		OBJECT-TYPE
			SYNTAX	INTEGER
			MAX-ACCESS	read-only
			STATUS	current
			::= { hmWanMbusA7 67 }

hmWanMbusA7VIF1F		OBJECT-TYPE
			SYNTAX	INTEGER
			MAX-ACCESS	read-only
			STATUS	current
			::= { hmWanMbusA7 68 }

hmWanMbusA7Value1F		OBJECT-TYPE
			SYNTAX	INTEGER
			MAX-ACCESS	read-only
			STATUS	current
			::= { hmWanMbusA7 69 }

hmWanMbusA7VIF20		OBJECT-TYPE
			SYNTAX	INTEGER
			MAX-ACCESS	read-only
			STATUS	current
			::= { hmWanMbusA7 70 }

hmWanMbusA7Value20		OBJECT-TYPE
			SYNTAX	INTEGER
			MAX-ACCESS	read-only
			STATUS	current
			::= { hmWanMbusA7 71 }

hmWanMbusA7VIF21		OBJECT-TYPE
			SYNTAX	INTEGER
			MAX-ACCESS	read-only
			STATUS	current
			::= { hmWanMbusA7 72 }

hmWanMbusA7Value21		OBJECT-TYPE
			SYNTAX	INTEGER
			MAX-ACCESS	read-only
			STATUS	current
			::= { hmWanMbusA7 73 }

hmWanMbusA7VIF22		OBJECT-TYPE
			SYNTAX	INTEGER
			MAX-ACCESS	read-only
			STATUS	current
			::= { hmWanMbusA7 74 }

hmWanMbusA7Value22		OBJECT-TYPE
			SYNTAX	INTEGER
			MAX-ACCESS	read-only
			STATUS	current
			::= { hmWanMbusA7 75 }

hmWanMbusA7VIF23		OBJECT-TYPE
			SYNTAX	INTEGER
			MAX-ACCESS	read-only
			STATUS	current
			::= { hmWanMbusA7 76 }

hmWanMbusA7Value23		OBJECT-TYPE
			SYNTAX	INTEGER
			MAX-ACCESS	read-only
			STATUS	current
			::= { hmWanMbusA7 77 }

hmWanMbusA7VIF24		OBJECT-TYPE
			SYNTAX	INTEGER
			MAX-ACCESS	read-only
			STATUS	current
			::= { hmWanMbusA7 78 }

hmWanMbusA7Value24		OBJECT-TYPE
			SYNTAX	INTEGER
			MAX-ACCESS	read-only
			STATUS	current
			::= { hmWanMbusA7 79 }

hmWanMbusA7VIF25		OBJECT-TYPE
			SYNTAX	INTEGER
			MAX-ACCESS	read-only
			STATUS	current
			::= { hmWanMbusA7 80 }

hmWanMbusA7Value25		OBJECT-TYPE
			SYNTAX	INTEGER
			MAX-ACCESS	read-only
			STATUS	current
			::= { hmWanMbusA7 81 }

hmWanMbusA7VIF26		OBJECT-TYPE
			SYNTAX	INTEGER
			MAX-ACCESS	read-only
			STATUS	current
			::= { hmWanMbusA7 82 }

hmWanMbusA7Value26		OBJECT-TYPE
			SYNTAX	INTEGER
			MAX-ACCESS	read-only
			STATUS	current
			::= { hmWanMbusA7 83 }

hmWanMbusA7VIF27		OBJECT-TYPE
			SYNTAX	INTEGER
			MAX-ACCESS	read-only
			STATUS	current
			::= { hmWanMbusA7 84 }

hmWanMbusA7Value27		OBJECT-TYPE
			SYNTAX	INTEGER
			MAX-ACCESS	read-only
			STATUS	current
			::= { hmWanMbusA7 85 }

hmWanMbusA7VIF28		OBJECT-TYPE
			SYNTAX	INTEGER
			MAX-ACCESS	read-only
			STATUS	current
			::= { hmWanMbusA7 86 }

hmWanMbusA7Value28		OBJECT-TYPE
			SYNTAX	INTEGER
			MAX-ACCESS	read-only
			STATUS	current
			::= { hmWanMbusA7 87 }

hmWanMbusA7VIF29		OBJECT-TYPE
			SYNTAX	INTEGER
			MAX-ACCESS	read-only
			STATUS	current
			::= { hmWanMbusA7 88 }

hmWanMbusA7Value29		OBJECT-TYPE
			SYNTAX	INTEGER
			MAX-ACCESS	read-only
			STATUS	current
			::= { hmWanMbusA7 89 }

hmWanMbusA7VIF2A		OBJECT-TYPE
			SYNTAX	INTEGER
			MAX-ACCESS	read-only
			STATUS	current
			::= { hmWanMbusA7 90 }

hmWanMbusA7Value2A		OBJECT-TYPE
			SYNTAX	INTEGER
			MAX-ACCESS	read-only
			STATUS	current
			::= { hmWanMbusA7 91 }

hmWanMbusA7VIF2B		OBJECT-TYPE
			SYNTAX	INTEGER
			MAX-ACCESS	read-only
			STATUS	current
			::= { hmWanMbusA7 92 }

hmWanMbusA7Value2B		OBJECT-TYPE
			SYNTAX	INTEGER
			MAX-ACCESS	read-only
			STATUS	current
			::= { hmWanMbusA7 93 }

hmWanMbusA7VIF2C		OBJECT-TYPE
			SYNTAX	INTEGER
			MAX-ACCESS	read-only
			STATUS	current
			::= { hmWanMbusA7 94 }

hmWanMbusA7Value2C		OBJECT-TYPE
			SYNTAX	INTEGER
			MAX-ACCESS	read-only
			STATUS	current
			::= { hmWanMbusA7 95 }

hmWanMbusA7VIF2D		OBJECT-TYPE
			SYNTAX	INTEGER
			MAX-ACCESS	read-only
			STATUS	current
			::= { hmWanMbusA7 96 }

hmWanMbusA7Value2D		OBJECT-TYPE
			SYNTAX	INTEGER
			MAX-ACCESS	read-only
			STATUS	current
			::= { hmWanMbusA7 97 }

hmWanMbusA7VIF2E		OBJECT-TYPE
			SYNTAX	INTEGER
			MAX-ACCESS	read-only
			STATUS	current
			::= { hmWanMbusA7 98 }

hmWanMbusA7Value2E		OBJECT-TYPE
			SYNTAX	INTEGER
			MAX-ACCESS	read-only
			STATUS	current
			::= { hmWanMbusA7 99 }

hmWanMbusA7VIF2F		OBJECT-TYPE
			SYNTAX	INTEGER
			MAX-ACCESS	read-only
			STATUS	current
			::= { hmWanMbusA7 100 }

hmWanMbusA7Value2F		OBJECT-TYPE
			SYNTAX	INTEGER
			MAX-ACCESS	read-only
			STATUS	current
			::= { hmWanMbusA7 101 }

hmWanMbusA8			OBJECT IDENTIFIER ::= { hmWanMbus 168 }

hmWanMbusA8IdNumber		OBJECT-TYPE
			SYNTAX	Gauge32
			MAX-ACCESS	read-only
			STATUS	current
			::= { hmWanMbusA8 1 }

hmWanMbusA8Manufacturer	OBJECT-TYPE
			SYNTAX	Gauge32
			MAX-ACCESS	read-only
			STATUS	current
			::= { hmWanMbusA8 2 }

hmWanMbusA8Version		OBJECT-TYPE
			SYNTAX	Gauge32
			MAX-ACCESS	read-only
			STATUS	current
			::= { hmWanMbusA8 3 }

hmWanMbusA8Medium		OBJECT-TYPE
			SYNTAX	Gauge32
			MAX-ACCESS	read-only
			STATUS	current
			::= { hmWanMbusA8 4 }

hmWanMbusA8Status		OBJECT-TYPE
			SYNTAX	Gauge32
			MAX-ACCESS	read-only
			STATUS	current
			::= { hmWanMbusA8 5 }

hmWanMbusA8VIF00		OBJECT-TYPE
			SYNTAX	INTEGER
			MAX-ACCESS	read-only
			STATUS	current
			::= { hmWanMbusA8 6 }

hmWanMbusA8Value00		OBJECT-TYPE
			SYNTAX	INTEGER
			MAX-ACCESS	read-only
			STATUS	current
			::= { hmWanMbusA8 7 }

hmWanMbusA8VIF01		OBJECT-TYPE
			SYNTAX	INTEGER
			MAX-ACCESS	read-only
			STATUS	current
			::= { hmWanMbusA8 8 }

hmWanMbusA8Value01		OBJECT-TYPE
			SYNTAX	INTEGER
			MAX-ACCESS	read-only
			STATUS	current
			::= { hmWanMbusA8 9 }

hmWanMbusA8VIF02		OBJECT-TYPE
			SYNTAX	INTEGER
			MAX-ACCESS	read-only
			STATUS	current
			::= { hmWanMbusA8 10 }

hmWanMbusA8Value02		OBJECT-TYPE
			SYNTAX	INTEGER
			MAX-ACCESS	read-only
			STATUS	current
			::= { hmWanMbusA8 11 }

hmWanMbusA8VIF03		OBJECT-TYPE
			SYNTAX	INTEGER
			MAX-ACCESS	read-only
			STATUS	current
			::= { hmWanMbusA8 12 }

hmWanMbusA8Value03		OBJECT-TYPE
			SYNTAX	INTEGER
			MAX-ACCESS	read-only
			STATUS	current
			::= { hmWanMbusA8 13 }

hmWanMbusA8VIF04		OBJECT-TYPE
			SYNTAX	INTEGER
			MAX-ACCESS	read-only
			STATUS	current
			::= { hmWanMbusA8 14 }

hmWanMbusA8Value04		OBJECT-TYPE
			SYNTAX	INTEGER
			MAX-ACCESS	read-only
			STATUS	current
			::= { hmWanMbusA8 15 }

hmWanMbusA8VIF05		OBJECT-TYPE
			SYNTAX	INTEGER
			MAX-ACCESS	read-only
			STATUS	current
			::= { hmWanMbusA8 16 }

hmWanMbusA8Value05		OBJECT-TYPE
			SYNTAX	INTEGER
			MAX-ACCESS	read-only
			STATUS	current
			::= { hmWanMbusA8 17 }

hmWanMbusA8VIF06		OBJECT-TYPE
			SYNTAX	INTEGER
			MAX-ACCESS	read-only
			STATUS	current
			::= { hmWanMbusA8 18 }

hmWanMbusA8Value06		OBJECT-TYPE
			SYNTAX	INTEGER
			MAX-ACCESS	read-only
			STATUS	current
			::= { hmWanMbusA8 19 }

hmWanMbusA8VIF07		OBJECT-TYPE
			SYNTAX	INTEGER
			MAX-ACCESS	read-only
			STATUS	current
			::= { hmWanMbusA8 20 }

hmWanMbusA8Value07		OBJECT-TYPE
			SYNTAX	INTEGER
			MAX-ACCESS	read-only
			STATUS	current
			::= { hmWanMbusA8 21 }

hmWanMbusA8VIF08		OBJECT-TYPE
			SYNTAX	INTEGER
			MAX-ACCESS	read-only
			STATUS	current
			::= { hmWanMbusA8 22 }

hmWanMbusA8Value08		OBJECT-TYPE
			SYNTAX	INTEGER
			MAX-ACCESS	read-only
			STATUS	current
			::= { hmWanMbusA8 23 }

hmWanMbusA8VIF09		OBJECT-TYPE
			SYNTAX	INTEGER
			MAX-ACCESS	read-only
			STATUS	current
			::= { hmWanMbusA8 24 }

hmWanMbusA8Value09		OBJECT-TYPE
			SYNTAX	INTEGER
			MAX-ACCESS	read-only
			STATUS	current
			::= { hmWanMbusA8 25 }

hmWanMbusA8VIF0A		OBJECT-TYPE
			SYNTAX	INTEGER
			MAX-ACCESS	read-only
			STATUS	current
			::= { hmWanMbusA8 26 }

hmWanMbusA8Value0A		OBJECT-TYPE
			SYNTAX	INTEGER
			MAX-ACCESS	read-only
			STATUS	current
			::= { hmWanMbusA8 27 }

hmWanMbusA8VIF0B		OBJECT-TYPE
			SYNTAX	INTEGER
			MAX-ACCESS	read-only
			STATUS	current
			::= { hmWanMbusA8 28 }

hmWanMbusA8Value0B		OBJECT-TYPE
			SYNTAX	INTEGER
			MAX-ACCESS	read-only
			STATUS	current
			::= { hmWanMbusA8 29 }

hmWanMbusA8VIF0C		OBJECT-TYPE
			SYNTAX	INTEGER
			MAX-ACCESS	read-only
			STATUS	current
			::= { hmWanMbusA8 30 }

hmWanMbusA8Value0C		OBJECT-TYPE
			SYNTAX	INTEGER
			MAX-ACCESS	read-only
			STATUS	current
			::= { hmWanMbusA8 31 }

hmWanMbusA8VIF0D		OBJECT-TYPE
			SYNTAX	INTEGER
			MAX-ACCESS	read-only
			STATUS	current
			::= { hmWanMbusA8 32 }

hmWanMbusA8Value0D		OBJECT-TYPE
			SYNTAX	INTEGER
			MAX-ACCESS	read-only
			STATUS	current
			::= { hmWanMbusA8 33 }

hmWanMbusA8VIF0E		OBJECT-TYPE
			SYNTAX	INTEGER
			MAX-ACCESS	read-only
			STATUS	current
			::= { hmWanMbusA8 34 }

hmWanMbusA8Value0E		OBJECT-TYPE
			SYNTAX	INTEGER
			MAX-ACCESS	read-only
			STATUS	current
			::= { hmWanMbusA8 35 }

hmWanMbusA8VIF0F		OBJECT-TYPE
			SYNTAX	INTEGER
			MAX-ACCESS	read-only
			STATUS	current
			::= { hmWanMbusA8 36 }

hmWanMbusA8Value0F		OBJECT-TYPE
			SYNTAX	INTEGER
			MAX-ACCESS	read-only
			STATUS	current
			::= { hmWanMbusA8 37 }

hmWanMbusA8VIF10		OBJECT-TYPE
			SYNTAX	INTEGER
			MAX-ACCESS	read-only
			STATUS	current
			::= { hmWanMbusA8 38 }

hmWanMbusA8Value10		OBJECT-TYPE
			SYNTAX	INTEGER
			MAX-ACCESS	read-only
			STATUS	current
			::= { hmWanMbusA8 39 }

hmWanMbusA8VIF11		OBJECT-TYPE
			SYNTAX	INTEGER
			MAX-ACCESS	read-only
			STATUS	current
			::= { hmWanMbusA8 40 }

hmWanMbusA8Value11		OBJECT-TYPE
			SYNTAX	INTEGER
			MAX-ACCESS	read-only
			STATUS	current
			::= { hmWanMbusA8 41 }

hmWanMbusA8VIF12		OBJECT-TYPE
			SYNTAX	INTEGER
			MAX-ACCESS	read-only
			STATUS	current
			::= { hmWanMbusA8 42 }

hmWanMbusA8Value12		OBJECT-TYPE
			SYNTAX	INTEGER
			MAX-ACCESS	read-only
			STATUS	current
			::= { hmWanMbusA8 43 }

hmWanMbusA8VIF13		OBJECT-TYPE
			SYNTAX	INTEGER
			MAX-ACCESS	read-only
			STATUS	current
			::= { hmWanMbusA8 44 }

hmWanMbusA8Value13		OBJECT-TYPE
			SYNTAX	INTEGER
			MAX-ACCESS	read-only
			STATUS	current
			::= { hmWanMbusA8 45 }

hmWanMbusA8VIF14		OBJECT-TYPE
			SYNTAX	INTEGER
			MAX-ACCESS	read-only
			STATUS	current
			::= { hmWanMbusA8 46 }

hmWanMbusA8Value14		OBJECT-TYPE
			SYNTAX	INTEGER
			MAX-ACCESS	read-only
			STATUS	current
			::= { hmWanMbusA8 47 }

hmWanMbusA8VIF15		OBJECT-TYPE
			SYNTAX	INTEGER
			MAX-ACCESS	read-only
			STATUS	current
			::= { hmWanMbusA8 48 }

hmWanMbusA8Value15		OBJECT-TYPE
			SYNTAX	INTEGER
			MAX-ACCESS	read-only
			STATUS	current
			::= { hmWanMbusA8 49 }

hmWanMbusA8VIF16		OBJECT-TYPE
			SYNTAX	INTEGER
			MAX-ACCESS	read-only
			STATUS	current
			::= { hmWanMbusA8 50 }

hmWanMbusA8Value16		OBJECT-TYPE
			SYNTAX	INTEGER
			MAX-ACCESS	read-only
			STATUS	current
			::= { hmWanMbusA8 51 }

hmWanMbusA8VIF17		OBJECT-TYPE
			SYNTAX	INTEGER
			MAX-ACCESS	read-only
			STATUS	current
			::= { hmWanMbusA8 52 }

hmWanMbusA8Value17		OBJECT-TYPE
			SYNTAX	INTEGER
			MAX-ACCESS	read-only
			STATUS	current
			::= { hmWanMbusA8 53 }

hmWanMbusA8VIF18		OBJECT-TYPE
			SYNTAX	INTEGER
			MAX-ACCESS	read-only
			STATUS	current
			::= { hmWanMbusA8 54 }

hmWanMbusA8Value18		OBJECT-TYPE
			SYNTAX	INTEGER
			MAX-ACCESS	read-only
			STATUS	current
			::= { hmWanMbusA8 55 }

hmWanMbusA8VIF19		OBJECT-TYPE
			SYNTAX	INTEGER
			MAX-ACCESS	read-only
			STATUS	current
			::= { hmWanMbusA8 56 }

hmWanMbusA8Value19		OBJECT-TYPE
			SYNTAX	INTEGER
			MAX-ACCESS	read-only
			STATUS	current
			::= { hmWanMbusA8 57 }

hmWanMbusA8VIF1A		OBJECT-TYPE
			SYNTAX	INTEGER
			MAX-ACCESS	read-only
			STATUS	current
			::= { hmWanMbusA8 58 }

hmWanMbusA8Value1A		OBJECT-TYPE
			SYNTAX	INTEGER
			MAX-ACCESS	read-only
			STATUS	current
			::= { hmWanMbusA8 59 }

hmWanMbusA8VIF1B		OBJECT-TYPE
			SYNTAX	INTEGER
			MAX-ACCESS	read-only
			STATUS	current
			::= { hmWanMbusA8 60 }

hmWanMbusA8Value1B		OBJECT-TYPE
			SYNTAX	INTEGER
			MAX-ACCESS	read-only
			STATUS	current
			::= { hmWanMbusA8 61 }

hmWanMbusA8VIF1C		OBJECT-TYPE
			SYNTAX	INTEGER
			MAX-ACCESS	read-only
			STATUS	current
			::= { hmWanMbusA8 62 }

hmWanMbusA8Value1C		OBJECT-TYPE
			SYNTAX	INTEGER
			MAX-ACCESS	read-only
			STATUS	current
			::= { hmWanMbusA8 63 }

hmWanMbusA8VIF1D		OBJECT-TYPE
			SYNTAX	INTEGER
			MAX-ACCESS	read-only
			STATUS	current
			::= { hmWanMbusA8 64 }

hmWanMbusA8Value1D		OBJECT-TYPE
			SYNTAX	INTEGER
			MAX-ACCESS	read-only
			STATUS	current
			::= { hmWanMbusA8 65 }

hmWanMbusA8VIF1E		OBJECT-TYPE
			SYNTAX	INTEGER
			MAX-ACCESS	read-only
			STATUS	current
			::= { hmWanMbusA8 66 }

hmWanMbusA8Value1E		OBJECT-TYPE
			SYNTAX	INTEGER
			MAX-ACCESS	read-only
			STATUS	current
			::= { hmWanMbusA8 67 }

hmWanMbusA8VIF1F		OBJECT-TYPE
			SYNTAX	INTEGER
			MAX-ACCESS	read-only
			STATUS	current
			::= { hmWanMbusA8 68 }

hmWanMbusA8Value1F		OBJECT-TYPE
			SYNTAX	INTEGER
			MAX-ACCESS	read-only
			STATUS	current
			::= { hmWanMbusA8 69 }

hmWanMbusA8VIF20		OBJECT-TYPE
			SYNTAX	INTEGER
			MAX-ACCESS	read-only
			STATUS	current
			::= { hmWanMbusA8 70 }

hmWanMbusA8Value20		OBJECT-TYPE
			SYNTAX	INTEGER
			MAX-ACCESS	read-only
			STATUS	current
			::= { hmWanMbusA8 71 }

hmWanMbusA8VIF21		OBJECT-TYPE
			SYNTAX	INTEGER
			MAX-ACCESS	read-only
			STATUS	current
			::= { hmWanMbusA8 72 }

hmWanMbusA8Value21		OBJECT-TYPE
			SYNTAX	INTEGER
			MAX-ACCESS	read-only
			STATUS	current
			::= { hmWanMbusA8 73 }

hmWanMbusA8VIF22		OBJECT-TYPE
			SYNTAX	INTEGER
			MAX-ACCESS	read-only
			STATUS	current
			::= { hmWanMbusA8 74 }

hmWanMbusA8Value22		OBJECT-TYPE
			SYNTAX	INTEGER
			MAX-ACCESS	read-only
			STATUS	current
			::= { hmWanMbusA8 75 }

hmWanMbusA8VIF23		OBJECT-TYPE
			SYNTAX	INTEGER
			MAX-ACCESS	read-only
			STATUS	current
			::= { hmWanMbusA8 76 }

hmWanMbusA8Value23		OBJECT-TYPE
			SYNTAX	INTEGER
			MAX-ACCESS	read-only
			STATUS	current
			::= { hmWanMbusA8 77 }

hmWanMbusA8VIF24		OBJECT-TYPE
			SYNTAX	INTEGER
			MAX-ACCESS	read-only
			STATUS	current
			::= { hmWanMbusA8 78 }

hmWanMbusA8Value24		OBJECT-TYPE
			SYNTAX	INTEGER
			MAX-ACCESS	read-only
			STATUS	current
			::= { hmWanMbusA8 79 }

hmWanMbusA8VIF25		OBJECT-TYPE
			SYNTAX	INTEGER
			MAX-ACCESS	read-only
			STATUS	current
			::= { hmWanMbusA8 80 }

hmWanMbusA8Value25		OBJECT-TYPE
			SYNTAX	INTEGER
			MAX-ACCESS	read-only
			STATUS	current
			::= { hmWanMbusA8 81 }

hmWanMbusA8VIF26		OBJECT-TYPE
			SYNTAX	INTEGER
			MAX-ACCESS	read-only
			STATUS	current
			::= { hmWanMbusA8 82 }

hmWanMbusA8Value26		OBJECT-TYPE
			SYNTAX	INTEGER
			MAX-ACCESS	read-only
			STATUS	current
			::= { hmWanMbusA8 83 }

hmWanMbusA8VIF27		OBJECT-TYPE
			SYNTAX	INTEGER
			MAX-ACCESS	read-only
			STATUS	current
			::= { hmWanMbusA8 84 }

hmWanMbusA8Value27		OBJECT-TYPE
			SYNTAX	INTEGER
			MAX-ACCESS	read-only
			STATUS	current
			::= { hmWanMbusA8 85 }

hmWanMbusA8VIF28		OBJECT-TYPE
			SYNTAX	INTEGER
			MAX-ACCESS	read-only
			STATUS	current
			::= { hmWanMbusA8 86 }

hmWanMbusA8Value28		OBJECT-TYPE
			SYNTAX	INTEGER
			MAX-ACCESS	read-only
			STATUS	current
			::= { hmWanMbusA8 87 }

hmWanMbusA8VIF29		OBJECT-TYPE
			SYNTAX	INTEGER
			MAX-ACCESS	read-only
			STATUS	current
			::= { hmWanMbusA8 88 }

hmWanMbusA8Value29		OBJECT-TYPE
			SYNTAX	INTEGER
			MAX-ACCESS	read-only
			STATUS	current
			::= { hmWanMbusA8 89 }

hmWanMbusA8VIF2A		OBJECT-TYPE
			SYNTAX	INTEGER
			MAX-ACCESS	read-only
			STATUS	current
			::= { hmWanMbusA8 90 }

hmWanMbusA8Value2A		OBJECT-TYPE
			SYNTAX	INTEGER
			MAX-ACCESS	read-only
			STATUS	current
			::= { hmWanMbusA8 91 }

hmWanMbusA8VIF2B		OBJECT-TYPE
			SYNTAX	INTEGER
			MAX-ACCESS	read-only
			STATUS	current
			::= { hmWanMbusA8 92 }

hmWanMbusA8Value2B		OBJECT-TYPE
			SYNTAX	INTEGER
			MAX-ACCESS	read-only
			STATUS	current
			::= { hmWanMbusA8 93 }

hmWanMbusA8VIF2C		OBJECT-TYPE
			SYNTAX	INTEGER
			MAX-ACCESS	read-only
			STATUS	current
			::= { hmWanMbusA8 94 }

hmWanMbusA8Value2C		OBJECT-TYPE
			SYNTAX	INTEGER
			MAX-ACCESS	read-only
			STATUS	current
			::= { hmWanMbusA8 95 }

hmWanMbusA8VIF2D		OBJECT-TYPE
			SYNTAX	INTEGER
			MAX-ACCESS	read-only
			STATUS	current
			::= { hmWanMbusA8 96 }

hmWanMbusA8Value2D		OBJECT-TYPE
			SYNTAX	INTEGER
			MAX-ACCESS	read-only
			STATUS	current
			::= { hmWanMbusA8 97 }

hmWanMbusA8VIF2E		OBJECT-TYPE
			SYNTAX	INTEGER
			MAX-ACCESS	read-only
			STATUS	current
			::= { hmWanMbusA8 98 }

hmWanMbusA8Value2E		OBJECT-TYPE
			SYNTAX	INTEGER
			MAX-ACCESS	read-only
			STATUS	current
			::= { hmWanMbusA8 99 }

hmWanMbusA8VIF2F		OBJECT-TYPE
			SYNTAX	INTEGER
			MAX-ACCESS	read-only
			STATUS	current
			::= { hmWanMbusA8 100 }

hmWanMbusA8Value2F		OBJECT-TYPE
			SYNTAX	INTEGER
			MAX-ACCESS	read-only
			STATUS	current
			::= { hmWanMbusA8 101 }

hmWanMbusA9			OBJECT IDENTIFIER ::= { hmWanMbus 169 }

hmWanMbusA9IdNumber		OBJECT-TYPE
			SYNTAX	Gauge32
			MAX-ACCESS	read-only
			STATUS	current
			::= { hmWanMbusA9 1 }

hmWanMbusA9Manufacturer	OBJECT-TYPE
			SYNTAX	Gauge32
			MAX-ACCESS	read-only
			STATUS	current
			::= { hmWanMbusA9 2 }

hmWanMbusA9Version		OBJECT-TYPE
			SYNTAX	Gauge32
			MAX-ACCESS	read-only
			STATUS	current
			::= { hmWanMbusA9 3 }

hmWanMbusA9Medium		OBJECT-TYPE
			SYNTAX	Gauge32
			MAX-ACCESS	read-only
			STATUS	current
			::= { hmWanMbusA9 4 }

hmWanMbusA9Status		OBJECT-TYPE
			SYNTAX	Gauge32
			MAX-ACCESS	read-only
			STATUS	current
			::= { hmWanMbusA9 5 }

hmWanMbusA9VIF00		OBJECT-TYPE
			SYNTAX	INTEGER
			MAX-ACCESS	read-only
			STATUS	current
			::= { hmWanMbusA9 6 }

hmWanMbusA9Value00		OBJECT-TYPE
			SYNTAX	INTEGER
			MAX-ACCESS	read-only
			STATUS	current
			::= { hmWanMbusA9 7 }

hmWanMbusA9VIF01		OBJECT-TYPE
			SYNTAX	INTEGER
			MAX-ACCESS	read-only
			STATUS	current
			::= { hmWanMbusA9 8 }

hmWanMbusA9Value01		OBJECT-TYPE
			SYNTAX	INTEGER
			MAX-ACCESS	read-only
			STATUS	current
			::= { hmWanMbusA9 9 }

hmWanMbusA9VIF02		OBJECT-TYPE
			SYNTAX	INTEGER
			MAX-ACCESS	read-only
			STATUS	current
			::= { hmWanMbusA9 10 }

hmWanMbusA9Value02		OBJECT-TYPE
			SYNTAX	INTEGER
			MAX-ACCESS	read-only
			STATUS	current
			::= { hmWanMbusA9 11 }

hmWanMbusA9VIF03		OBJECT-TYPE
			SYNTAX	INTEGER
			MAX-ACCESS	read-only
			STATUS	current
			::= { hmWanMbusA9 12 }

hmWanMbusA9Value03		OBJECT-TYPE
			SYNTAX	INTEGER
			MAX-ACCESS	read-only
			STATUS	current
			::= { hmWanMbusA9 13 }

hmWanMbusA9VIF04		OBJECT-TYPE
			SYNTAX	INTEGER
			MAX-ACCESS	read-only
			STATUS	current
			::= { hmWanMbusA9 14 }

hmWanMbusA9Value04		OBJECT-TYPE
			SYNTAX	INTEGER
			MAX-ACCESS	read-only
			STATUS	current
			::= { hmWanMbusA9 15 }

hmWanMbusA9VIF05		OBJECT-TYPE
			SYNTAX	INTEGER
			MAX-ACCESS	read-only
			STATUS	current
			::= { hmWanMbusA9 16 }

hmWanMbusA9Value05		OBJECT-TYPE
			SYNTAX	INTEGER
			MAX-ACCESS	read-only
			STATUS	current
			::= { hmWanMbusA9 17 }

hmWanMbusA9VIF06		OBJECT-TYPE
			SYNTAX	INTEGER
			MAX-ACCESS	read-only
			STATUS	current
			::= { hmWanMbusA9 18 }

hmWanMbusA9Value06		OBJECT-TYPE
			SYNTAX	INTEGER
			MAX-ACCESS	read-only
			STATUS	current
			::= { hmWanMbusA9 19 }

hmWanMbusA9VIF07		OBJECT-TYPE
			SYNTAX	INTEGER
			MAX-ACCESS	read-only
			STATUS	current
			::= { hmWanMbusA9 20 }

hmWanMbusA9Value07		OBJECT-TYPE
			SYNTAX	INTEGER
			MAX-ACCESS	read-only
			STATUS	current
			::= { hmWanMbusA9 21 }

hmWanMbusA9VIF08		OBJECT-TYPE
			SYNTAX	INTEGER
			MAX-ACCESS	read-only
			STATUS	current
			::= { hmWanMbusA9 22 }

hmWanMbusA9Value08		OBJECT-TYPE
			SYNTAX	INTEGER
			MAX-ACCESS	read-only
			STATUS	current
			::= { hmWanMbusA9 23 }

hmWanMbusA9VIF09		OBJECT-TYPE
			SYNTAX	INTEGER
			MAX-ACCESS	read-only
			STATUS	current
			::= { hmWanMbusA9 24 }

hmWanMbusA9Value09		OBJECT-TYPE
			SYNTAX	INTEGER
			MAX-ACCESS	read-only
			STATUS	current
			::= { hmWanMbusA9 25 }

hmWanMbusA9VIF0A		OBJECT-TYPE
			SYNTAX	INTEGER
			MAX-ACCESS	read-only
			STATUS	current
			::= { hmWanMbusA9 26 }

hmWanMbusA9Value0A		OBJECT-TYPE
			SYNTAX	INTEGER
			MAX-ACCESS	read-only
			STATUS	current
			::= { hmWanMbusA9 27 }

hmWanMbusA9VIF0B		OBJECT-TYPE
			SYNTAX	INTEGER
			MAX-ACCESS	read-only
			STATUS	current
			::= { hmWanMbusA9 28 }

hmWanMbusA9Value0B		OBJECT-TYPE
			SYNTAX	INTEGER
			MAX-ACCESS	read-only
			STATUS	current
			::= { hmWanMbusA9 29 }

hmWanMbusA9VIF0C		OBJECT-TYPE
			SYNTAX	INTEGER
			MAX-ACCESS	read-only
			STATUS	current
			::= { hmWanMbusA9 30 }

hmWanMbusA9Value0C		OBJECT-TYPE
			SYNTAX	INTEGER
			MAX-ACCESS	read-only
			STATUS	current
			::= { hmWanMbusA9 31 }

hmWanMbusA9VIF0D		OBJECT-TYPE
			SYNTAX	INTEGER
			MAX-ACCESS	read-only
			STATUS	current
			::= { hmWanMbusA9 32 }

hmWanMbusA9Value0D		OBJECT-TYPE
			SYNTAX	INTEGER
			MAX-ACCESS	read-only
			STATUS	current
			::= { hmWanMbusA9 33 }

hmWanMbusA9VIF0E		OBJECT-TYPE
			SYNTAX	INTEGER
			MAX-ACCESS	read-only
			STATUS	current
			::= { hmWanMbusA9 34 }

hmWanMbusA9Value0E		OBJECT-TYPE
			SYNTAX	INTEGER
			MAX-ACCESS	read-only
			STATUS	current
			::= { hmWanMbusA9 35 }

hmWanMbusA9VIF0F		OBJECT-TYPE
			SYNTAX	INTEGER
			MAX-ACCESS	read-only
			STATUS	current
			::= { hmWanMbusA9 36 }

hmWanMbusA9Value0F		OBJECT-TYPE
			SYNTAX	INTEGER
			MAX-ACCESS	read-only
			STATUS	current
			::= { hmWanMbusA9 37 }

hmWanMbusA9VIF10		OBJECT-TYPE
			SYNTAX	INTEGER
			MAX-ACCESS	read-only
			STATUS	current
			::= { hmWanMbusA9 38 }

hmWanMbusA9Value10		OBJECT-TYPE
			SYNTAX	INTEGER
			MAX-ACCESS	read-only
			STATUS	current
			::= { hmWanMbusA9 39 }

hmWanMbusA9VIF11		OBJECT-TYPE
			SYNTAX	INTEGER
			MAX-ACCESS	read-only
			STATUS	current
			::= { hmWanMbusA9 40 }

hmWanMbusA9Value11		OBJECT-TYPE
			SYNTAX	INTEGER
			MAX-ACCESS	read-only
			STATUS	current
			::= { hmWanMbusA9 41 }

hmWanMbusA9VIF12		OBJECT-TYPE
			SYNTAX	INTEGER
			MAX-ACCESS	read-only
			STATUS	current
			::= { hmWanMbusA9 42 }

hmWanMbusA9Value12		OBJECT-TYPE
			SYNTAX	INTEGER
			MAX-ACCESS	read-only
			STATUS	current
			::= { hmWanMbusA9 43 }

hmWanMbusA9VIF13		OBJECT-TYPE
			SYNTAX	INTEGER
			MAX-ACCESS	read-only
			STATUS	current
			::= { hmWanMbusA9 44 }

hmWanMbusA9Value13		OBJECT-TYPE
			SYNTAX	INTEGER
			MAX-ACCESS	read-only
			STATUS	current
			::= { hmWanMbusA9 45 }

hmWanMbusA9VIF14		OBJECT-TYPE
			SYNTAX	INTEGER
			MAX-ACCESS	read-only
			STATUS	current
			::= { hmWanMbusA9 46 }

hmWanMbusA9Value14		OBJECT-TYPE
			SYNTAX	INTEGER
			MAX-ACCESS	read-only
			STATUS	current
			::= { hmWanMbusA9 47 }

hmWanMbusA9VIF15		OBJECT-TYPE
			SYNTAX	INTEGER
			MAX-ACCESS	read-only
			STATUS	current
			::= { hmWanMbusA9 48 }

hmWanMbusA9Value15		OBJECT-TYPE
			SYNTAX	INTEGER
			MAX-ACCESS	read-only
			STATUS	current
			::= { hmWanMbusA9 49 }

hmWanMbusA9VIF16		OBJECT-TYPE
			SYNTAX	INTEGER
			MAX-ACCESS	read-only
			STATUS	current
			::= { hmWanMbusA9 50 }

hmWanMbusA9Value16		OBJECT-TYPE
			SYNTAX	INTEGER
			MAX-ACCESS	read-only
			STATUS	current
			::= { hmWanMbusA9 51 }

hmWanMbusA9VIF17		OBJECT-TYPE
			SYNTAX	INTEGER
			MAX-ACCESS	read-only
			STATUS	current
			::= { hmWanMbusA9 52 }

hmWanMbusA9Value17		OBJECT-TYPE
			SYNTAX	INTEGER
			MAX-ACCESS	read-only
			STATUS	current
			::= { hmWanMbusA9 53 }

hmWanMbusA9VIF18		OBJECT-TYPE
			SYNTAX	INTEGER
			MAX-ACCESS	read-only
			STATUS	current
			::= { hmWanMbusA9 54 }

hmWanMbusA9Value18		OBJECT-TYPE
			SYNTAX	INTEGER
			MAX-ACCESS	read-only
			STATUS	current
			::= { hmWanMbusA9 55 }

hmWanMbusA9VIF19		OBJECT-TYPE
			SYNTAX	INTEGER
			MAX-ACCESS	read-only
			STATUS	current
			::= { hmWanMbusA9 56 }

hmWanMbusA9Value19		OBJECT-TYPE
			SYNTAX	INTEGER
			MAX-ACCESS	read-only
			STATUS	current
			::= { hmWanMbusA9 57 }

hmWanMbusA9VIF1A		OBJECT-TYPE
			SYNTAX	INTEGER
			MAX-ACCESS	read-only
			STATUS	current
			::= { hmWanMbusA9 58 }

hmWanMbusA9Value1A		OBJECT-TYPE
			SYNTAX	INTEGER
			MAX-ACCESS	read-only
			STATUS	current
			::= { hmWanMbusA9 59 }

hmWanMbusA9VIF1B		OBJECT-TYPE
			SYNTAX	INTEGER
			MAX-ACCESS	read-only
			STATUS	current
			::= { hmWanMbusA9 60 }

hmWanMbusA9Value1B		OBJECT-TYPE
			SYNTAX	INTEGER
			MAX-ACCESS	read-only
			STATUS	current
			::= { hmWanMbusA9 61 }

hmWanMbusA9VIF1C		OBJECT-TYPE
			SYNTAX	INTEGER
			MAX-ACCESS	read-only
			STATUS	current
			::= { hmWanMbusA9 62 }

hmWanMbusA9Value1C		OBJECT-TYPE
			SYNTAX	INTEGER
			MAX-ACCESS	read-only
			STATUS	current
			::= { hmWanMbusA9 63 }

hmWanMbusA9VIF1D		OBJECT-TYPE
			SYNTAX	INTEGER
			MAX-ACCESS	read-only
			STATUS	current
			::= { hmWanMbusA9 64 }

hmWanMbusA9Value1D		OBJECT-TYPE
			SYNTAX	INTEGER
			MAX-ACCESS	read-only
			STATUS	current
			::= { hmWanMbusA9 65 }

hmWanMbusA9VIF1E		OBJECT-TYPE
			SYNTAX	INTEGER
			MAX-ACCESS	read-only
			STATUS	current
			::= { hmWanMbusA9 66 }

hmWanMbusA9Value1E		OBJECT-TYPE
			SYNTAX	INTEGER
			MAX-ACCESS	read-only
			STATUS	current
			::= { hmWanMbusA9 67 }

hmWanMbusA9VIF1F		OBJECT-TYPE
			SYNTAX	INTEGER
			MAX-ACCESS	read-only
			STATUS	current
			::= { hmWanMbusA9 68 }

hmWanMbusA9Value1F		OBJECT-TYPE
			SYNTAX	INTEGER
			MAX-ACCESS	read-only
			STATUS	current
			::= { hmWanMbusA9 69 }

hmWanMbusA9VIF20		OBJECT-TYPE
			SYNTAX	INTEGER
			MAX-ACCESS	read-only
			STATUS	current
			::= { hmWanMbusA9 70 }

hmWanMbusA9Value20		OBJECT-TYPE
			SYNTAX	INTEGER
			MAX-ACCESS	read-only
			STATUS	current
			::= { hmWanMbusA9 71 }

hmWanMbusA9VIF21		OBJECT-TYPE
			SYNTAX	INTEGER
			MAX-ACCESS	read-only
			STATUS	current
			::= { hmWanMbusA9 72 }

hmWanMbusA9Value21		OBJECT-TYPE
			SYNTAX	INTEGER
			MAX-ACCESS	read-only
			STATUS	current
			::= { hmWanMbusA9 73 }

hmWanMbusA9VIF22		OBJECT-TYPE
			SYNTAX	INTEGER
			MAX-ACCESS	read-only
			STATUS	current
			::= { hmWanMbusA9 74 }

hmWanMbusA9Value22		OBJECT-TYPE
			SYNTAX	INTEGER
			MAX-ACCESS	read-only
			STATUS	current
			::= { hmWanMbusA9 75 }

hmWanMbusA9VIF23		OBJECT-TYPE
			SYNTAX	INTEGER
			MAX-ACCESS	read-only
			STATUS	current
			::= { hmWanMbusA9 76 }

hmWanMbusA9Value23		OBJECT-TYPE
			SYNTAX	INTEGER
			MAX-ACCESS	read-only
			STATUS	current
			::= { hmWanMbusA9 77 }

hmWanMbusA9VIF24		OBJECT-TYPE
			SYNTAX	INTEGER
			MAX-ACCESS	read-only
			STATUS	current
			::= { hmWanMbusA9 78 }

hmWanMbusA9Value24		OBJECT-TYPE
			SYNTAX	INTEGER
			MAX-ACCESS	read-only
			STATUS	current
			::= { hmWanMbusA9 79 }

hmWanMbusA9VIF25		OBJECT-TYPE
			SYNTAX	INTEGER
			MAX-ACCESS	read-only
			STATUS	current
			::= { hmWanMbusA9 80 }

hmWanMbusA9Value25		OBJECT-TYPE
			SYNTAX	INTEGER
			MAX-ACCESS	read-only
			STATUS	current
			::= { hmWanMbusA9 81 }

hmWanMbusA9VIF26		OBJECT-TYPE
			SYNTAX	INTEGER
			MAX-ACCESS	read-only
			STATUS	current
			::= { hmWanMbusA9 82 }

hmWanMbusA9Value26		OBJECT-TYPE
			SYNTAX	INTEGER
			MAX-ACCESS	read-only
			STATUS	current
			::= { hmWanMbusA9 83 }

hmWanMbusA9VIF27		OBJECT-TYPE
			SYNTAX	INTEGER
			MAX-ACCESS	read-only
			STATUS	current
			::= { hmWanMbusA9 84 }

hmWanMbusA9Value27		OBJECT-TYPE
			SYNTAX	INTEGER
			MAX-ACCESS	read-only
			STATUS	current
			::= { hmWanMbusA9 85 }

hmWanMbusA9VIF28		OBJECT-TYPE
			SYNTAX	INTEGER
			MAX-ACCESS	read-only
			STATUS	current
			::= { hmWanMbusA9 86 }

hmWanMbusA9Value28		OBJECT-TYPE
			SYNTAX	INTEGER
			MAX-ACCESS	read-only
			STATUS	current
			::= { hmWanMbusA9 87 }

hmWanMbusA9VIF29		OBJECT-TYPE
			SYNTAX	INTEGER
			MAX-ACCESS	read-only
			STATUS	current
			::= { hmWanMbusA9 88 }

hmWanMbusA9Value29		OBJECT-TYPE
			SYNTAX	INTEGER
			MAX-ACCESS	read-only
			STATUS	current
			::= { hmWanMbusA9 89 }

hmWanMbusA9VIF2A		OBJECT-TYPE
			SYNTAX	INTEGER
			MAX-ACCESS	read-only
			STATUS	current
			::= { hmWanMbusA9 90 }

hmWanMbusA9Value2A		OBJECT-TYPE
			SYNTAX	INTEGER
			MAX-ACCESS	read-only
			STATUS	current
			::= { hmWanMbusA9 91 }

hmWanMbusA9VIF2B		OBJECT-TYPE
			SYNTAX	INTEGER
			MAX-ACCESS	read-only
			STATUS	current
			::= { hmWanMbusA9 92 }

hmWanMbusA9Value2B		OBJECT-TYPE
			SYNTAX	INTEGER
			MAX-ACCESS	read-only
			STATUS	current
			::= { hmWanMbusA9 93 }

hmWanMbusA9VIF2C		OBJECT-TYPE
			SYNTAX	INTEGER
			MAX-ACCESS	read-only
			STATUS	current
			::= { hmWanMbusA9 94 }

hmWanMbusA9Value2C		OBJECT-TYPE
			SYNTAX	INTEGER
			MAX-ACCESS	read-only
			STATUS	current
			::= { hmWanMbusA9 95 }

hmWanMbusA9VIF2D		OBJECT-TYPE
			SYNTAX	INTEGER
			MAX-ACCESS	read-only
			STATUS	current
			::= { hmWanMbusA9 96 }

hmWanMbusA9Value2D		OBJECT-TYPE
			SYNTAX	INTEGER
			MAX-ACCESS	read-only
			STATUS	current
			::= { hmWanMbusA9 97 }

hmWanMbusA9VIF2E		OBJECT-TYPE
			SYNTAX	INTEGER
			MAX-ACCESS	read-only
			STATUS	current
			::= { hmWanMbusA9 98 }

hmWanMbusA9Value2E		OBJECT-TYPE
			SYNTAX	INTEGER
			MAX-ACCESS	read-only
			STATUS	current
			::= { hmWanMbusA9 99 }

hmWanMbusA9VIF2F		OBJECT-TYPE
			SYNTAX	INTEGER
			MAX-ACCESS	read-only
			STATUS	current
			::= { hmWanMbusA9 100 }

hmWanMbusA9Value2F		OBJECT-TYPE
			SYNTAX	INTEGER
			MAX-ACCESS	read-only
			STATUS	current
			::= { hmWanMbusA9 101 }

hmWanMbusAA			OBJECT IDENTIFIER ::= { hmWanMbus 170 }

hmWanMbusAAIdNumber		OBJECT-TYPE
			SYNTAX	Gauge32
			MAX-ACCESS	read-only
			STATUS	current
			::= { hmWanMbusAA 1 }

hmWanMbusAAManufacturer	OBJECT-TYPE
			SYNTAX	Gauge32
			MAX-ACCESS	read-only
			STATUS	current
			::= { hmWanMbusAA 2 }

hmWanMbusAAVersion		OBJECT-TYPE
			SYNTAX	Gauge32
			MAX-ACCESS	read-only
			STATUS	current
			::= { hmWanMbusAA 3 }

hmWanMbusAAMedium		OBJECT-TYPE
			SYNTAX	Gauge32
			MAX-ACCESS	read-only
			STATUS	current
			::= { hmWanMbusAA 4 }

hmWanMbusAAStatus		OBJECT-TYPE
			SYNTAX	Gauge32
			MAX-ACCESS	read-only
			STATUS	current
			::= { hmWanMbusAA 5 }

hmWanMbusAAVIF00		OBJECT-TYPE
			SYNTAX	INTEGER
			MAX-ACCESS	read-only
			STATUS	current
			::= { hmWanMbusAA 6 }

hmWanMbusAAValue00		OBJECT-TYPE
			SYNTAX	INTEGER
			MAX-ACCESS	read-only
			STATUS	current
			::= { hmWanMbusAA 7 }

hmWanMbusAAVIF01		OBJECT-TYPE
			SYNTAX	INTEGER
			MAX-ACCESS	read-only
			STATUS	current
			::= { hmWanMbusAA 8 }

hmWanMbusAAValue01		OBJECT-TYPE
			SYNTAX	INTEGER
			MAX-ACCESS	read-only
			STATUS	current
			::= { hmWanMbusAA 9 }

hmWanMbusAAVIF02		OBJECT-TYPE
			SYNTAX	INTEGER
			MAX-ACCESS	read-only
			STATUS	current
			::= { hmWanMbusAA 10 }

hmWanMbusAAValue02		OBJECT-TYPE
			SYNTAX	INTEGER
			MAX-ACCESS	read-only
			STATUS	current
			::= { hmWanMbusAA 11 }

hmWanMbusAAVIF03		OBJECT-TYPE
			SYNTAX	INTEGER
			MAX-ACCESS	read-only
			STATUS	current
			::= { hmWanMbusAA 12 }

hmWanMbusAAValue03		OBJECT-TYPE
			SYNTAX	INTEGER
			MAX-ACCESS	read-only
			STATUS	current
			::= { hmWanMbusAA 13 }

hmWanMbusAAVIF04		OBJECT-TYPE
			SYNTAX	INTEGER
			MAX-ACCESS	read-only
			STATUS	current
			::= { hmWanMbusAA 14 }

hmWanMbusAAValue04		OBJECT-TYPE
			SYNTAX	INTEGER
			MAX-ACCESS	read-only
			STATUS	current
			::= { hmWanMbusAA 15 }

hmWanMbusAAVIF05		OBJECT-TYPE
			SYNTAX	INTEGER
			MAX-ACCESS	read-only
			STATUS	current
			::= { hmWanMbusAA 16 }

hmWanMbusAAValue05		OBJECT-TYPE
			SYNTAX	INTEGER
			MAX-ACCESS	read-only
			STATUS	current
			::= { hmWanMbusAA 17 }

hmWanMbusAAVIF06		OBJECT-TYPE
			SYNTAX	INTEGER
			MAX-ACCESS	read-only
			STATUS	current
			::= { hmWanMbusAA 18 }

hmWanMbusAAValue06		OBJECT-TYPE
			SYNTAX	INTEGER
			MAX-ACCESS	read-only
			STATUS	current
			::= { hmWanMbusAA 19 }

hmWanMbusAAVIF07		OBJECT-TYPE
			SYNTAX	INTEGER
			MAX-ACCESS	read-only
			STATUS	current
			::= { hmWanMbusAA 20 }

hmWanMbusAAValue07		OBJECT-TYPE
			SYNTAX	INTEGER
			MAX-ACCESS	read-only
			STATUS	current
			::= { hmWanMbusAA 21 }

hmWanMbusAAVIF08		OBJECT-TYPE
			SYNTAX	INTEGER
			MAX-ACCESS	read-only
			STATUS	current
			::= { hmWanMbusAA 22 }

hmWanMbusAAValue08		OBJECT-TYPE
			SYNTAX	INTEGER
			MAX-ACCESS	read-only
			STATUS	current
			::= { hmWanMbusAA 23 }

hmWanMbusAAVIF09		OBJECT-TYPE
			SYNTAX	INTEGER
			MAX-ACCESS	read-only
			STATUS	current
			::= { hmWanMbusAA 24 }

hmWanMbusAAValue09		OBJECT-TYPE
			SYNTAX	INTEGER
			MAX-ACCESS	read-only
			STATUS	current
			::= { hmWanMbusAA 25 }

hmWanMbusAAVIF0A		OBJECT-TYPE
			SYNTAX	INTEGER
			MAX-ACCESS	read-only
			STATUS	current
			::= { hmWanMbusAA 26 }

hmWanMbusAAValue0A		OBJECT-TYPE
			SYNTAX	INTEGER
			MAX-ACCESS	read-only
			STATUS	current
			::= { hmWanMbusAA 27 }

hmWanMbusAAVIF0B		OBJECT-TYPE
			SYNTAX	INTEGER
			MAX-ACCESS	read-only
			STATUS	current
			::= { hmWanMbusAA 28 }

hmWanMbusAAValue0B		OBJECT-TYPE
			SYNTAX	INTEGER
			MAX-ACCESS	read-only
			STATUS	current
			::= { hmWanMbusAA 29 }

hmWanMbusAAVIF0C		OBJECT-TYPE
			SYNTAX	INTEGER
			MAX-ACCESS	read-only
			STATUS	current
			::= { hmWanMbusAA 30 }

hmWanMbusAAValue0C		OBJECT-TYPE
			SYNTAX	INTEGER
			MAX-ACCESS	read-only
			STATUS	current
			::= { hmWanMbusAA 31 }

hmWanMbusAAVIF0D		OBJECT-TYPE
			SYNTAX	INTEGER
			MAX-ACCESS	read-only
			STATUS	current
			::= { hmWanMbusAA 32 }

hmWanMbusAAValue0D		OBJECT-TYPE
			SYNTAX	INTEGER
			MAX-ACCESS	read-only
			STATUS	current
			::= { hmWanMbusAA 33 }

hmWanMbusAAVIF0E		OBJECT-TYPE
			SYNTAX	INTEGER
			MAX-ACCESS	read-only
			STATUS	current
			::= { hmWanMbusAA 34 }

hmWanMbusAAValue0E		OBJECT-TYPE
			SYNTAX	INTEGER
			MAX-ACCESS	read-only
			STATUS	current
			::= { hmWanMbusAA 35 }

hmWanMbusAAVIF0F		OBJECT-TYPE
			SYNTAX	INTEGER
			MAX-ACCESS	read-only
			STATUS	current
			::= { hmWanMbusAA 36 }

hmWanMbusAAValue0F		OBJECT-TYPE
			SYNTAX	INTEGER
			MAX-ACCESS	read-only
			STATUS	current
			::= { hmWanMbusAA 37 }

hmWanMbusAAVIF10		OBJECT-TYPE
			SYNTAX	INTEGER
			MAX-ACCESS	read-only
			STATUS	current
			::= { hmWanMbusAA 38 }

hmWanMbusAAValue10		OBJECT-TYPE
			SYNTAX	INTEGER
			MAX-ACCESS	read-only
			STATUS	current
			::= { hmWanMbusAA 39 }

hmWanMbusAAVIF11		OBJECT-TYPE
			SYNTAX	INTEGER
			MAX-ACCESS	read-only
			STATUS	current
			::= { hmWanMbusAA 40 }

hmWanMbusAAValue11		OBJECT-TYPE
			SYNTAX	INTEGER
			MAX-ACCESS	read-only
			STATUS	current
			::= { hmWanMbusAA 41 }

hmWanMbusAAVIF12		OBJECT-TYPE
			SYNTAX	INTEGER
			MAX-ACCESS	read-only
			STATUS	current
			::= { hmWanMbusAA 42 }

hmWanMbusAAValue12		OBJECT-TYPE
			SYNTAX	INTEGER
			MAX-ACCESS	read-only
			STATUS	current
			::= { hmWanMbusAA 43 }

hmWanMbusAAVIF13		OBJECT-TYPE
			SYNTAX	INTEGER
			MAX-ACCESS	read-only
			STATUS	current
			::= { hmWanMbusAA 44 }

hmWanMbusAAValue13		OBJECT-TYPE
			SYNTAX	INTEGER
			MAX-ACCESS	read-only
			STATUS	current
			::= { hmWanMbusAA 45 }

hmWanMbusAAVIF14		OBJECT-TYPE
			SYNTAX	INTEGER
			MAX-ACCESS	read-only
			STATUS	current
			::= { hmWanMbusAA 46 }

hmWanMbusAAValue14		OBJECT-TYPE
			SYNTAX	INTEGER
			MAX-ACCESS	read-only
			STATUS	current
			::= { hmWanMbusAA 47 }

hmWanMbusAAVIF15		OBJECT-TYPE
			SYNTAX	INTEGER
			MAX-ACCESS	read-only
			STATUS	current
			::= { hmWanMbusAA 48 }

hmWanMbusAAValue15		OBJECT-TYPE
			SYNTAX	INTEGER
			MAX-ACCESS	read-only
			STATUS	current
			::= { hmWanMbusAA 49 }

hmWanMbusAAVIF16		OBJECT-TYPE
			SYNTAX	INTEGER
			MAX-ACCESS	read-only
			STATUS	current
			::= { hmWanMbusAA 50 }

hmWanMbusAAValue16		OBJECT-TYPE
			SYNTAX	INTEGER
			MAX-ACCESS	read-only
			STATUS	current
			::= { hmWanMbusAA 51 }

hmWanMbusAAVIF17		OBJECT-TYPE
			SYNTAX	INTEGER
			MAX-ACCESS	read-only
			STATUS	current
			::= { hmWanMbusAA 52 }

hmWanMbusAAValue17		OBJECT-TYPE
			SYNTAX	INTEGER
			MAX-ACCESS	read-only
			STATUS	current
			::= { hmWanMbusAA 53 }

hmWanMbusAAVIF18		OBJECT-TYPE
			SYNTAX	INTEGER
			MAX-ACCESS	read-only
			STATUS	current
			::= { hmWanMbusAA 54 }

hmWanMbusAAValue18		OBJECT-TYPE
			SYNTAX	INTEGER
			MAX-ACCESS	read-only
			STATUS	current
			::= { hmWanMbusAA 55 }

hmWanMbusAAVIF19		OBJECT-TYPE
			SYNTAX	INTEGER
			MAX-ACCESS	read-only
			STATUS	current
			::= { hmWanMbusAA 56 }

hmWanMbusAAValue19		OBJECT-TYPE
			SYNTAX	INTEGER
			MAX-ACCESS	read-only
			STATUS	current
			::= { hmWanMbusAA 57 }

hmWanMbusAAVIF1A		OBJECT-TYPE
			SYNTAX	INTEGER
			MAX-ACCESS	read-only
			STATUS	current
			::= { hmWanMbusAA 58 }

hmWanMbusAAValue1A		OBJECT-TYPE
			SYNTAX	INTEGER
			MAX-ACCESS	read-only
			STATUS	current
			::= { hmWanMbusAA 59 }

hmWanMbusAAVIF1B		OBJECT-TYPE
			SYNTAX	INTEGER
			MAX-ACCESS	read-only
			STATUS	current
			::= { hmWanMbusAA 60 }

hmWanMbusAAValue1B		OBJECT-TYPE
			SYNTAX	INTEGER
			MAX-ACCESS	read-only
			STATUS	current
			::= { hmWanMbusAA 61 }

hmWanMbusAAVIF1C		OBJECT-TYPE
			SYNTAX	INTEGER
			MAX-ACCESS	read-only
			STATUS	current
			::= { hmWanMbusAA 62 }

hmWanMbusAAValue1C		OBJECT-TYPE
			SYNTAX	INTEGER
			MAX-ACCESS	read-only
			STATUS	current
			::= { hmWanMbusAA 63 }

hmWanMbusAAVIF1D		OBJECT-TYPE
			SYNTAX	INTEGER
			MAX-ACCESS	read-only
			STATUS	current
			::= { hmWanMbusAA 64 }

hmWanMbusAAValue1D		OBJECT-TYPE
			SYNTAX	INTEGER
			MAX-ACCESS	read-only
			STATUS	current
			::= { hmWanMbusAA 65 }

hmWanMbusAAVIF1E		OBJECT-TYPE
			SYNTAX	INTEGER
			MAX-ACCESS	read-only
			STATUS	current
			::= { hmWanMbusAA 66 }

hmWanMbusAAValue1E		OBJECT-TYPE
			SYNTAX	INTEGER
			MAX-ACCESS	read-only
			STATUS	current
			::= { hmWanMbusAA 67 }

hmWanMbusAAVIF1F		OBJECT-TYPE
			SYNTAX	INTEGER
			MAX-ACCESS	read-only
			STATUS	current
			::= { hmWanMbusAA 68 }

hmWanMbusAAValue1F		OBJECT-TYPE
			SYNTAX	INTEGER
			MAX-ACCESS	read-only
			STATUS	current
			::= { hmWanMbusAA 69 }

hmWanMbusAAVIF20		OBJECT-TYPE
			SYNTAX	INTEGER
			MAX-ACCESS	read-only
			STATUS	current
			::= { hmWanMbusAA 70 }

hmWanMbusAAValue20		OBJECT-TYPE
			SYNTAX	INTEGER
			MAX-ACCESS	read-only
			STATUS	current
			::= { hmWanMbusAA 71 }

hmWanMbusAAVIF21		OBJECT-TYPE
			SYNTAX	INTEGER
			MAX-ACCESS	read-only
			STATUS	current
			::= { hmWanMbusAA 72 }

hmWanMbusAAValue21		OBJECT-TYPE
			SYNTAX	INTEGER
			MAX-ACCESS	read-only
			STATUS	current
			::= { hmWanMbusAA 73 }

hmWanMbusAAVIF22		OBJECT-TYPE
			SYNTAX	INTEGER
			MAX-ACCESS	read-only
			STATUS	current
			::= { hmWanMbusAA 74 }

hmWanMbusAAValue22		OBJECT-TYPE
			SYNTAX	INTEGER
			MAX-ACCESS	read-only
			STATUS	current
			::= { hmWanMbusAA 75 }

hmWanMbusAAVIF23		OBJECT-TYPE
			SYNTAX	INTEGER
			MAX-ACCESS	read-only
			STATUS	current
			::= { hmWanMbusAA 76 }

hmWanMbusAAValue23		OBJECT-TYPE
			SYNTAX	INTEGER
			MAX-ACCESS	read-only
			STATUS	current
			::= { hmWanMbusAA 77 }

hmWanMbusAAVIF24		OBJECT-TYPE
			SYNTAX	INTEGER
			MAX-ACCESS	read-only
			STATUS	current
			::= { hmWanMbusAA 78 }

hmWanMbusAAValue24		OBJECT-TYPE
			SYNTAX	INTEGER
			MAX-ACCESS	read-only
			STATUS	current
			::= { hmWanMbusAA 79 }

hmWanMbusAAVIF25		OBJECT-TYPE
			SYNTAX	INTEGER
			MAX-ACCESS	read-only
			STATUS	current
			::= { hmWanMbusAA 80 }

hmWanMbusAAValue25		OBJECT-TYPE
			SYNTAX	INTEGER
			MAX-ACCESS	read-only
			STATUS	current
			::= { hmWanMbusAA 81 }

hmWanMbusAAVIF26		OBJECT-TYPE
			SYNTAX	INTEGER
			MAX-ACCESS	read-only
			STATUS	current
			::= { hmWanMbusAA 82 }

hmWanMbusAAValue26		OBJECT-TYPE
			SYNTAX	INTEGER
			MAX-ACCESS	read-only
			STATUS	current
			::= { hmWanMbusAA 83 }

hmWanMbusAAVIF27		OBJECT-TYPE
			SYNTAX	INTEGER
			MAX-ACCESS	read-only
			STATUS	current
			::= { hmWanMbusAA 84 }

hmWanMbusAAValue27		OBJECT-TYPE
			SYNTAX	INTEGER
			MAX-ACCESS	read-only
			STATUS	current
			::= { hmWanMbusAA 85 }

hmWanMbusAAVIF28		OBJECT-TYPE
			SYNTAX	INTEGER
			MAX-ACCESS	read-only
			STATUS	current
			::= { hmWanMbusAA 86 }

hmWanMbusAAValue28		OBJECT-TYPE
			SYNTAX	INTEGER
			MAX-ACCESS	read-only
			STATUS	current
			::= { hmWanMbusAA 87 }

hmWanMbusAAVIF29		OBJECT-TYPE
			SYNTAX	INTEGER
			MAX-ACCESS	read-only
			STATUS	current
			::= { hmWanMbusAA 88 }

hmWanMbusAAValue29		OBJECT-TYPE
			SYNTAX	INTEGER
			MAX-ACCESS	read-only
			STATUS	current
			::= { hmWanMbusAA 89 }

hmWanMbusAAVIF2A		OBJECT-TYPE
			SYNTAX	INTEGER
			MAX-ACCESS	read-only
			STATUS	current
			::= { hmWanMbusAA 90 }

hmWanMbusAAValue2A		OBJECT-TYPE
			SYNTAX	INTEGER
			MAX-ACCESS	read-only
			STATUS	current
			::= { hmWanMbusAA 91 }

hmWanMbusAAVIF2B		OBJECT-TYPE
			SYNTAX	INTEGER
			MAX-ACCESS	read-only
			STATUS	current
			::= { hmWanMbusAA 92 }

hmWanMbusAAValue2B		OBJECT-TYPE
			SYNTAX	INTEGER
			MAX-ACCESS	read-only
			STATUS	current
			::= { hmWanMbusAA 93 }

hmWanMbusAAVIF2C		OBJECT-TYPE
			SYNTAX	INTEGER
			MAX-ACCESS	read-only
			STATUS	current
			::= { hmWanMbusAA 94 }

hmWanMbusAAValue2C		OBJECT-TYPE
			SYNTAX	INTEGER
			MAX-ACCESS	read-only
			STATUS	current
			::= { hmWanMbusAA 95 }

hmWanMbusAAVIF2D		OBJECT-TYPE
			SYNTAX	INTEGER
			MAX-ACCESS	read-only
			STATUS	current
			::= { hmWanMbusAA 96 }

hmWanMbusAAValue2D		OBJECT-TYPE
			SYNTAX	INTEGER
			MAX-ACCESS	read-only
			STATUS	current
			::= { hmWanMbusAA 97 }

hmWanMbusAAVIF2E		OBJECT-TYPE
			SYNTAX	INTEGER
			MAX-ACCESS	read-only
			STATUS	current
			::= { hmWanMbusAA 98 }

hmWanMbusAAValue2E		OBJECT-TYPE
			SYNTAX	INTEGER
			MAX-ACCESS	read-only
			STATUS	current
			::= { hmWanMbusAA 99 }

hmWanMbusAAVIF2F		OBJECT-TYPE
			SYNTAX	INTEGER
			MAX-ACCESS	read-only
			STATUS	current
			::= { hmWanMbusAA 100 }

hmWanMbusAAValue2F		OBJECT-TYPE
			SYNTAX	INTEGER
			MAX-ACCESS	read-only
			STATUS	current
			::= { hmWanMbusAA 101 }

hmWanMbusAB			OBJECT IDENTIFIER ::= { hmWanMbus 171 }

hmWanMbusABIdNumber		OBJECT-TYPE
			SYNTAX	Gauge32
			MAX-ACCESS	read-only
			STATUS	current
			::= { hmWanMbusAB 1 }

hmWanMbusABManufacturer	OBJECT-TYPE
			SYNTAX	Gauge32
			MAX-ACCESS	read-only
			STATUS	current
			::= { hmWanMbusAB 2 }

hmWanMbusABVersion		OBJECT-TYPE
			SYNTAX	Gauge32
			MAX-ACCESS	read-only
			STATUS	current
			::= { hmWanMbusAB 3 }

hmWanMbusABMedium		OBJECT-TYPE
			SYNTAX	Gauge32
			MAX-ACCESS	read-only
			STATUS	current
			::= { hmWanMbusAB 4 }

hmWanMbusABStatus		OBJECT-TYPE
			SYNTAX	Gauge32
			MAX-ACCESS	read-only
			STATUS	current
			::= { hmWanMbusAB 5 }

hmWanMbusABVIF00		OBJECT-TYPE
			SYNTAX	INTEGER
			MAX-ACCESS	read-only
			STATUS	current
			::= { hmWanMbusAB 6 }

hmWanMbusABValue00		OBJECT-TYPE
			SYNTAX	INTEGER
			MAX-ACCESS	read-only
			STATUS	current
			::= { hmWanMbusAB 7 }

hmWanMbusABVIF01		OBJECT-TYPE
			SYNTAX	INTEGER
			MAX-ACCESS	read-only
			STATUS	current
			::= { hmWanMbusAB 8 }

hmWanMbusABValue01		OBJECT-TYPE
			SYNTAX	INTEGER
			MAX-ACCESS	read-only
			STATUS	current
			::= { hmWanMbusAB 9 }

hmWanMbusABVIF02		OBJECT-TYPE
			SYNTAX	INTEGER
			MAX-ACCESS	read-only
			STATUS	current
			::= { hmWanMbusAB 10 }

hmWanMbusABValue02		OBJECT-TYPE
			SYNTAX	INTEGER
			MAX-ACCESS	read-only
			STATUS	current
			::= { hmWanMbusAB 11 }

hmWanMbusABVIF03		OBJECT-TYPE
			SYNTAX	INTEGER
			MAX-ACCESS	read-only
			STATUS	current
			::= { hmWanMbusAB 12 }

hmWanMbusABValue03		OBJECT-TYPE
			SYNTAX	INTEGER
			MAX-ACCESS	read-only
			STATUS	current
			::= { hmWanMbusAB 13 }

hmWanMbusABVIF04		OBJECT-TYPE
			SYNTAX	INTEGER
			MAX-ACCESS	read-only
			STATUS	current
			::= { hmWanMbusAB 14 }

hmWanMbusABValue04		OBJECT-TYPE
			SYNTAX	INTEGER
			MAX-ACCESS	read-only
			STATUS	current
			::= { hmWanMbusAB 15 }

hmWanMbusABVIF05		OBJECT-TYPE
			SYNTAX	INTEGER
			MAX-ACCESS	read-only
			STATUS	current
			::= { hmWanMbusAB 16 }

hmWanMbusABValue05		OBJECT-TYPE
			SYNTAX	INTEGER
			MAX-ACCESS	read-only
			STATUS	current
			::= { hmWanMbusAB 17 }

hmWanMbusABVIF06		OBJECT-TYPE
			SYNTAX	INTEGER
			MAX-ACCESS	read-only
			STATUS	current
			::= { hmWanMbusAB 18 }

hmWanMbusABValue06		OBJECT-TYPE
			SYNTAX	INTEGER
			MAX-ACCESS	read-only
			STATUS	current
			::= { hmWanMbusAB 19 }

hmWanMbusABVIF07		OBJECT-TYPE
			SYNTAX	INTEGER
			MAX-ACCESS	read-only
			STATUS	current
			::= { hmWanMbusAB 20 }

hmWanMbusABValue07		OBJECT-TYPE
			SYNTAX	INTEGER
			MAX-ACCESS	read-only
			STATUS	current
			::= { hmWanMbusAB 21 }

hmWanMbusABVIF08		OBJECT-TYPE
			SYNTAX	INTEGER
			MAX-ACCESS	read-only
			STATUS	current
			::= { hmWanMbusAB 22 }

hmWanMbusABValue08		OBJECT-TYPE
			SYNTAX	INTEGER
			MAX-ACCESS	read-only
			STATUS	current
			::= { hmWanMbusAB 23 }

hmWanMbusABVIF09		OBJECT-TYPE
			SYNTAX	INTEGER
			MAX-ACCESS	read-only
			STATUS	current
			::= { hmWanMbusAB 24 }

hmWanMbusABValue09		OBJECT-TYPE
			SYNTAX	INTEGER
			MAX-ACCESS	read-only
			STATUS	current
			::= { hmWanMbusAB 25 }

hmWanMbusABVIF0A		OBJECT-TYPE
			SYNTAX	INTEGER
			MAX-ACCESS	read-only
			STATUS	current
			::= { hmWanMbusAB 26 }

hmWanMbusABValue0A		OBJECT-TYPE
			SYNTAX	INTEGER
			MAX-ACCESS	read-only
			STATUS	current
			::= { hmWanMbusAB 27 }

hmWanMbusABVIF0B		OBJECT-TYPE
			SYNTAX	INTEGER
			MAX-ACCESS	read-only
			STATUS	current
			::= { hmWanMbusAB 28 }

hmWanMbusABValue0B		OBJECT-TYPE
			SYNTAX	INTEGER
			MAX-ACCESS	read-only
			STATUS	current
			::= { hmWanMbusAB 29 }

hmWanMbusABVIF0C		OBJECT-TYPE
			SYNTAX	INTEGER
			MAX-ACCESS	read-only
			STATUS	current
			::= { hmWanMbusAB 30 }

hmWanMbusABValue0C		OBJECT-TYPE
			SYNTAX	INTEGER
			MAX-ACCESS	read-only
			STATUS	current
			::= { hmWanMbusAB 31 }

hmWanMbusABVIF0D		OBJECT-TYPE
			SYNTAX	INTEGER
			MAX-ACCESS	read-only
			STATUS	current
			::= { hmWanMbusAB 32 }

hmWanMbusABValue0D		OBJECT-TYPE
			SYNTAX	INTEGER
			MAX-ACCESS	read-only
			STATUS	current
			::= { hmWanMbusAB 33 }

hmWanMbusABVIF0E		OBJECT-TYPE
			SYNTAX	INTEGER
			MAX-ACCESS	read-only
			STATUS	current
			::= { hmWanMbusAB 34 }

hmWanMbusABValue0E		OBJECT-TYPE
			SYNTAX	INTEGER
			MAX-ACCESS	read-only
			STATUS	current
			::= { hmWanMbusAB 35 }

hmWanMbusABVIF0F		OBJECT-TYPE
			SYNTAX	INTEGER
			MAX-ACCESS	read-only
			STATUS	current
			::= { hmWanMbusAB 36 }

hmWanMbusABValue0F		OBJECT-TYPE
			SYNTAX	INTEGER
			MAX-ACCESS	read-only
			STATUS	current
			::= { hmWanMbusAB 37 }

hmWanMbusABVIF10		OBJECT-TYPE
			SYNTAX	INTEGER
			MAX-ACCESS	read-only
			STATUS	current
			::= { hmWanMbusAB 38 }

hmWanMbusABValue10		OBJECT-TYPE
			SYNTAX	INTEGER
			MAX-ACCESS	read-only
			STATUS	current
			::= { hmWanMbusAB 39 }

hmWanMbusABVIF11		OBJECT-TYPE
			SYNTAX	INTEGER
			MAX-ACCESS	read-only
			STATUS	current
			::= { hmWanMbusAB 40 }

hmWanMbusABValue11		OBJECT-TYPE
			SYNTAX	INTEGER
			MAX-ACCESS	read-only
			STATUS	current
			::= { hmWanMbusAB 41 }

hmWanMbusABVIF12		OBJECT-TYPE
			SYNTAX	INTEGER
			MAX-ACCESS	read-only
			STATUS	current
			::= { hmWanMbusAB 42 }

hmWanMbusABValue12		OBJECT-TYPE
			SYNTAX	INTEGER
			MAX-ACCESS	read-only
			STATUS	current
			::= { hmWanMbusAB 43 }

hmWanMbusABVIF13		OBJECT-TYPE
			SYNTAX	INTEGER
			MAX-ACCESS	read-only
			STATUS	current
			::= { hmWanMbusAB 44 }

hmWanMbusABValue13		OBJECT-TYPE
			SYNTAX	INTEGER
			MAX-ACCESS	read-only
			STATUS	current
			::= { hmWanMbusAB 45 }

hmWanMbusABVIF14		OBJECT-TYPE
			SYNTAX	INTEGER
			MAX-ACCESS	read-only
			STATUS	current
			::= { hmWanMbusAB 46 }

hmWanMbusABValue14		OBJECT-TYPE
			SYNTAX	INTEGER
			MAX-ACCESS	read-only
			STATUS	current
			::= { hmWanMbusAB 47 }

hmWanMbusABVIF15		OBJECT-TYPE
			SYNTAX	INTEGER
			MAX-ACCESS	read-only
			STATUS	current
			::= { hmWanMbusAB 48 }

hmWanMbusABValue15		OBJECT-TYPE
			SYNTAX	INTEGER
			MAX-ACCESS	read-only
			STATUS	current
			::= { hmWanMbusAB 49 }

hmWanMbusABVIF16		OBJECT-TYPE
			SYNTAX	INTEGER
			MAX-ACCESS	read-only
			STATUS	current
			::= { hmWanMbusAB 50 }

hmWanMbusABValue16		OBJECT-TYPE
			SYNTAX	INTEGER
			MAX-ACCESS	read-only
			STATUS	current
			::= { hmWanMbusAB 51 }

hmWanMbusABVIF17		OBJECT-TYPE
			SYNTAX	INTEGER
			MAX-ACCESS	read-only
			STATUS	current
			::= { hmWanMbusAB 52 }

hmWanMbusABValue17		OBJECT-TYPE
			SYNTAX	INTEGER
			MAX-ACCESS	read-only
			STATUS	current
			::= { hmWanMbusAB 53 }

hmWanMbusABVIF18		OBJECT-TYPE
			SYNTAX	INTEGER
			MAX-ACCESS	read-only
			STATUS	current
			::= { hmWanMbusAB 54 }

hmWanMbusABValue18		OBJECT-TYPE
			SYNTAX	INTEGER
			MAX-ACCESS	read-only
			STATUS	current
			::= { hmWanMbusAB 55 }

hmWanMbusABVIF19		OBJECT-TYPE
			SYNTAX	INTEGER
			MAX-ACCESS	read-only
			STATUS	current
			::= { hmWanMbusAB 56 }

hmWanMbusABValue19		OBJECT-TYPE
			SYNTAX	INTEGER
			MAX-ACCESS	read-only
			STATUS	current
			::= { hmWanMbusAB 57 }

hmWanMbusABVIF1A		OBJECT-TYPE
			SYNTAX	INTEGER
			MAX-ACCESS	read-only
			STATUS	current
			::= { hmWanMbusAB 58 }

hmWanMbusABValue1A		OBJECT-TYPE
			SYNTAX	INTEGER
			MAX-ACCESS	read-only
			STATUS	current
			::= { hmWanMbusAB 59 }

hmWanMbusABVIF1B		OBJECT-TYPE
			SYNTAX	INTEGER
			MAX-ACCESS	read-only
			STATUS	current
			::= { hmWanMbusAB 60 }

hmWanMbusABValue1B		OBJECT-TYPE
			SYNTAX	INTEGER
			MAX-ACCESS	read-only
			STATUS	current
			::= { hmWanMbusAB 61 }

hmWanMbusABVIF1C		OBJECT-TYPE
			SYNTAX	INTEGER
			MAX-ACCESS	read-only
			STATUS	current
			::= { hmWanMbusAB 62 }

hmWanMbusABValue1C		OBJECT-TYPE
			SYNTAX	INTEGER
			MAX-ACCESS	read-only
			STATUS	current
			::= { hmWanMbusAB 63 }

hmWanMbusABVIF1D		OBJECT-TYPE
			SYNTAX	INTEGER
			MAX-ACCESS	read-only
			STATUS	current
			::= { hmWanMbusAB 64 }

hmWanMbusABValue1D		OBJECT-TYPE
			SYNTAX	INTEGER
			MAX-ACCESS	read-only
			STATUS	current
			::= { hmWanMbusAB 65 }

hmWanMbusABVIF1E		OBJECT-TYPE
			SYNTAX	INTEGER
			MAX-ACCESS	read-only
			STATUS	current
			::= { hmWanMbusAB 66 }

hmWanMbusABValue1E		OBJECT-TYPE
			SYNTAX	INTEGER
			MAX-ACCESS	read-only
			STATUS	current
			::= { hmWanMbusAB 67 }

hmWanMbusABVIF1F		OBJECT-TYPE
			SYNTAX	INTEGER
			MAX-ACCESS	read-only
			STATUS	current
			::= { hmWanMbusAB 68 }

hmWanMbusABValue1F		OBJECT-TYPE
			SYNTAX	INTEGER
			MAX-ACCESS	read-only
			STATUS	current
			::= { hmWanMbusAB 69 }

hmWanMbusABVIF20		OBJECT-TYPE
			SYNTAX	INTEGER
			MAX-ACCESS	read-only
			STATUS	current
			::= { hmWanMbusAB 70 }

hmWanMbusABValue20		OBJECT-TYPE
			SYNTAX	INTEGER
			MAX-ACCESS	read-only
			STATUS	current
			::= { hmWanMbusAB 71 }

hmWanMbusABVIF21		OBJECT-TYPE
			SYNTAX	INTEGER
			MAX-ACCESS	read-only
			STATUS	current
			::= { hmWanMbusAB 72 }

hmWanMbusABValue21		OBJECT-TYPE
			SYNTAX	INTEGER
			MAX-ACCESS	read-only
			STATUS	current
			::= { hmWanMbusAB 73 }

hmWanMbusABVIF22		OBJECT-TYPE
			SYNTAX	INTEGER
			MAX-ACCESS	read-only
			STATUS	current
			::= { hmWanMbusAB 74 }

hmWanMbusABValue22		OBJECT-TYPE
			SYNTAX	INTEGER
			MAX-ACCESS	read-only
			STATUS	current
			::= { hmWanMbusAB 75 }

hmWanMbusABVIF23		OBJECT-TYPE
			SYNTAX	INTEGER
			MAX-ACCESS	read-only
			STATUS	current
			::= { hmWanMbusAB 76 }

hmWanMbusABValue23		OBJECT-TYPE
			SYNTAX	INTEGER
			MAX-ACCESS	read-only
			STATUS	current
			::= { hmWanMbusAB 77 }

hmWanMbusABVIF24		OBJECT-TYPE
			SYNTAX	INTEGER
			MAX-ACCESS	read-only
			STATUS	current
			::= { hmWanMbusAB 78 }

hmWanMbusABValue24		OBJECT-TYPE
			SYNTAX	INTEGER
			MAX-ACCESS	read-only
			STATUS	current
			::= { hmWanMbusAB 79 }

hmWanMbusABVIF25		OBJECT-TYPE
			SYNTAX	INTEGER
			MAX-ACCESS	read-only
			STATUS	current
			::= { hmWanMbusAB 80 }

hmWanMbusABValue25		OBJECT-TYPE
			SYNTAX	INTEGER
			MAX-ACCESS	read-only
			STATUS	current
			::= { hmWanMbusAB 81 }

hmWanMbusABVIF26		OBJECT-TYPE
			SYNTAX	INTEGER
			MAX-ACCESS	read-only
			STATUS	current
			::= { hmWanMbusAB 82 }

hmWanMbusABValue26		OBJECT-TYPE
			SYNTAX	INTEGER
			MAX-ACCESS	read-only
			STATUS	current
			::= { hmWanMbusAB 83 }

hmWanMbusABVIF27		OBJECT-TYPE
			SYNTAX	INTEGER
			MAX-ACCESS	read-only
			STATUS	current
			::= { hmWanMbusAB 84 }

hmWanMbusABValue27		OBJECT-TYPE
			SYNTAX	INTEGER
			MAX-ACCESS	read-only
			STATUS	current
			::= { hmWanMbusAB 85 }

hmWanMbusABVIF28		OBJECT-TYPE
			SYNTAX	INTEGER
			MAX-ACCESS	read-only
			STATUS	current
			::= { hmWanMbusAB 86 }

hmWanMbusABValue28		OBJECT-TYPE
			SYNTAX	INTEGER
			MAX-ACCESS	read-only
			STATUS	current
			::= { hmWanMbusAB 87 }

hmWanMbusABVIF29		OBJECT-TYPE
			SYNTAX	INTEGER
			MAX-ACCESS	read-only
			STATUS	current
			::= { hmWanMbusAB 88 }

hmWanMbusABValue29		OBJECT-TYPE
			SYNTAX	INTEGER
			MAX-ACCESS	read-only
			STATUS	current
			::= { hmWanMbusAB 89 }

hmWanMbusABVIF2A		OBJECT-TYPE
			SYNTAX	INTEGER
			MAX-ACCESS	read-only
			STATUS	current
			::= { hmWanMbusAB 90 }

hmWanMbusABValue2A		OBJECT-TYPE
			SYNTAX	INTEGER
			MAX-ACCESS	read-only
			STATUS	current
			::= { hmWanMbusAB 91 }

hmWanMbusABVIF2B		OBJECT-TYPE
			SYNTAX	INTEGER
			MAX-ACCESS	read-only
			STATUS	current
			::= { hmWanMbusAB 92 }

hmWanMbusABValue2B		OBJECT-TYPE
			SYNTAX	INTEGER
			MAX-ACCESS	read-only
			STATUS	current
			::= { hmWanMbusAB 93 }

hmWanMbusABVIF2C		OBJECT-TYPE
			SYNTAX	INTEGER
			MAX-ACCESS	read-only
			STATUS	current
			::= { hmWanMbusAB 94 }

hmWanMbusABValue2C		OBJECT-TYPE
			SYNTAX	INTEGER
			MAX-ACCESS	read-only
			STATUS	current
			::= { hmWanMbusAB 95 }

hmWanMbusABVIF2D		OBJECT-TYPE
			SYNTAX	INTEGER
			MAX-ACCESS	read-only
			STATUS	current
			::= { hmWanMbusAB 96 }

hmWanMbusABValue2D		OBJECT-TYPE
			SYNTAX	INTEGER
			MAX-ACCESS	read-only
			STATUS	current
			::= { hmWanMbusAB 97 }

hmWanMbusABVIF2E		OBJECT-TYPE
			SYNTAX	INTEGER
			MAX-ACCESS	read-only
			STATUS	current
			::= { hmWanMbusAB 98 }

hmWanMbusABValue2E		OBJECT-TYPE
			SYNTAX	INTEGER
			MAX-ACCESS	read-only
			STATUS	current
			::= { hmWanMbusAB 99 }

hmWanMbusABVIF2F		OBJECT-TYPE
			SYNTAX	INTEGER
			MAX-ACCESS	read-only
			STATUS	current
			::= { hmWanMbusAB 100 }

hmWanMbusABValue2F		OBJECT-TYPE
			SYNTAX	INTEGER
			MAX-ACCESS	read-only
			STATUS	current
			::= { hmWanMbusAB 101 }

hmWanMbusAC			OBJECT IDENTIFIER ::= { hmWanMbus 172 }

hmWanMbusACIdNumber		OBJECT-TYPE
			SYNTAX	Gauge32
			MAX-ACCESS	read-only
			STATUS	current
			::= { hmWanMbusAC 1 }

hmWanMbusACManufacturer	OBJECT-TYPE
			SYNTAX	Gauge32
			MAX-ACCESS	read-only
			STATUS	current
			::= { hmWanMbusAC 2 }

hmWanMbusACVersion		OBJECT-TYPE
			SYNTAX	Gauge32
			MAX-ACCESS	read-only
			STATUS	current
			::= { hmWanMbusAC 3 }

hmWanMbusACMedium		OBJECT-TYPE
			SYNTAX	Gauge32
			MAX-ACCESS	read-only
			STATUS	current
			::= { hmWanMbusAC 4 }

hmWanMbusACStatus		OBJECT-TYPE
			SYNTAX	Gauge32
			MAX-ACCESS	read-only
			STATUS	current
			::= { hmWanMbusAC 5 }

hmWanMbusACVIF00		OBJECT-TYPE
			SYNTAX	INTEGER
			MAX-ACCESS	read-only
			STATUS	current
			::= { hmWanMbusAC 6 }

hmWanMbusACValue00		OBJECT-TYPE
			SYNTAX	INTEGER
			MAX-ACCESS	read-only
			STATUS	current
			::= { hmWanMbusAC 7 }

hmWanMbusACVIF01		OBJECT-TYPE
			SYNTAX	INTEGER
			MAX-ACCESS	read-only
			STATUS	current
			::= { hmWanMbusAC 8 }

hmWanMbusACValue01		OBJECT-TYPE
			SYNTAX	INTEGER
			MAX-ACCESS	read-only
			STATUS	current
			::= { hmWanMbusAC 9 }

hmWanMbusACVIF02		OBJECT-TYPE
			SYNTAX	INTEGER
			MAX-ACCESS	read-only
			STATUS	current
			::= { hmWanMbusAC 10 }

hmWanMbusACValue02		OBJECT-TYPE
			SYNTAX	INTEGER
			MAX-ACCESS	read-only
			STATUS	current
			::= { hmWanMbusAC 11 }

hmWanMbusACVIF03		OBJECT-TYPE
			SYNTAX	INTEGER
			MAX-ACCESS	read-only
			STATUS	current
			::= { hmWanMbusAC 12 }

hmWanMbusACValue03		OBJECT-TYPE
			SYNTAX	INTEGER
			MAX-ACCESS	read-only
			STATUS	current
			::= { hmWanMbusAC 13 }

hmWanMbusACVIF04		OBJECT-TYPE
			SYNTAX	INTEGER
			MAX-ACCESS	read-only
			STATUS	current
			::= { hmWanMbusAC 14 }

hmWanMbusACValue04		OBJECT-TYPE
			SYNTAX	INTEGER
			MAX-ACCESS	read-only
			STATUS	current
			::= { hmWanMbusAC 15 }

hmWanMbusACVIF05		OBJECT-TYPE
			SYNTAX	INTEGER
			MAX-ACCESS	read-only
			STATUS	current
			::= { hmWanMbusAC 16 }

hmWanMbusACValue05		OBJECT-TYPE
			SYNTAX	INTEGER
			MAX-ACCESS	read-only
			STATUS	current
			::= { hmWanMbusAC 17 }

hmWanMbusACVIF06		OBJECT-TYPE
			SYNTAX	INTEGER
			MAX-ACCESS	read-only
			STATUS	current
			::= { hmWanMbusAC 18 }

hmWanMbusACValue06		OBJECT-TYPE
			SYNTAX	INTEGER
			MAX-ACCESS	read-only
			STATUS	current
			::= { hmWanMbusAC 19 }

hmWanMbusACVIF07		OBJECT-TYPE
			SYNTAX	INTEGER
			MAX-ACCESS	read-only
			STATUS	current
			::= { hmWanMbusAC 20 }

hmWanMbusACValue07		OBJECT-TYPE
			SYNTAX	INTEGER
			MAX-ACCESS	read-only
			STATUS	current
			::= { hmWanMbusAC 21 }

hmWanMbusACVIF08		OBJECT-TYPE
			SYNTAX	INTEGER
			MAX-ACCESS	read-only
			STATUS	current
			::= { hmWanMbusAC 22 }

hmWanMbusACValue08		OBJECT-TYPE
			SYNTAX	INTEGER
			MAX-ACCESS	read-only
			STATUS	current
			::= { hmWanMbusAC 23 }

hmWanMbusACVIF09		OBJECT-TYPE
			SYNTAX	INTEGER
			MAX-ACCESS	read-only
			STATUS	current
			::= { hmWanMbusAC 24 }

hmWanMbusACValue09		OBJECT-TYPE
			SYNTAX	INTEGER
			MAX-ACCESS	read-only
			STATUS	current
			::= { hmWanMbusAC 25 }

hmWanMbusACVIF0A		OBJECT-TYPE
			SYNTAX	INTEGER
			MAX-ACCESS	read-only
			STATUS	current
			::= { hmWanMbusAC 26 }

hmWanMbusACValue0A		OBJECT-TYPE
			SYNTAX	INTEGER
			MAX-ACCESS	read-only
			STATUS	current
			::= { hmWanMbusAC 27 }

hmWanMbusACVIF0B		OBJECT-TYPE
			SYNTAX	INTEGER
			MAX-ACCESS	read-only
			STATUS	current
			::= { hmWanMbusAC 28 }

hmWanMbusACValue0B		OBJECT-TYPE
			SYNTAX	INTEGER
			MAX-ACCESS	read-only
			STATUS	current
			::= { hmWanMbusAC 29 }

hmWanMbusACVIF0C		OBJECT-TYPE
			SYNTAX	INTEGER
			MAX-ACCESS	read-only
			STATUS	current
			::= { hmWanMbusAC 30 }

hmWanMbusACValue0C		OBJECT-TYPE
			SYNTAX	INTEGER
			MAX-ACCESS	read-only
			STATUS	current
			::= { hmWanMbusAC 31 }

hmWanMbusACVIF0D		OBJECT-TYPE
			SYNTAX	INTEGER
			MAX-ACCESS	read-only
			STATUS	current
			::= { hmWanMbusAC 32 }

hmWanMbusACValue0D		OBJECT-TYPE
			SYNTAX	INTEGER
			MAX-ACCESS	read-only
			STATUS	current
			::= { hmWanMbusAC 33 }

hmWanMbusACVIF0E		OBJECT-TYPE
			SYNTAX	INTEGER
			MAX-ACCESS	read-only
			STATUS	current
			::= { hmWanMbusAC 34 }

hmWanMbusACValue0E		OBJECT-TYPE
			SYNTAX	INTEGER
			MAX-ACCESS	read-only
			STATUS	current
			::= { hmWanMbusAC 35 }

hmWanMbusACVIF0F		OBJECT-TYPE
			SYNTAX	INTEGER
			MAX-ACCESS	read-only
			STATUS	current
			::= { hmWanMbusAC 36 }

hmWanMbusACValue0F		OBJECT-TYPE
			SYNTAX	INTEGER
			MAX-ACCESS	read-only
			STATUS	current
			::= { hmWanMbusAC 37 }

hmWanMbusACVIF10		OBJECT-TYPE
			SYNTAX	INTEGER
			MAX-ACCESS	read-only
			STATUS	current
			::= { hmWanMbusAC 38 }

hmWanMbusACValue10		OBJECT-TYPE
			SYNTAX	INTEGER
			MAX-ACCESS	read-only
			STATUS	current
			::= { hmWanMbusAC 39 }

hmWanMbusACVIF11		OBJECT-TYPE
			SYNTAX	INTEGER
			MAX-ACCESS	read-only
			STATUS	current
			::= { hmWanMbusAC 40 }

hmWanMbusACValue11		OBJECT-TYPE
			SYNTAX	INTEGER
			MAX-ACCESS	read-only
			STATUS	current
			::= { hmWanMbusAC 41 }

hmWanMbusACVIF12		OBJECT-TYPE
			SYNTAX	INTEGER
			MAX-ACCESS	read-only
			STATUS	current
			::= { hmWanMbusAC 42 }

hmWanMbusACValue12		OBJECT-TYPE
			SYNTAX	INTEGER
			MAX-ACCESS	read-only
			STATUS	current
			::= { hmWanMbusAC 43 }

hmWanMbusACVIF13		OBJECT-TYPE
			SYNTAX	INTEGER
			MAX-ACCESS	read-only
			STATUS	current
			::= { hmWanMbusAC 44 }

hmWanMbusACValue13		OBJECT-TYPE
			SYNTAX	INTEGER
			MAX-ACCESS	read-only
			STATUS	current
			::= { hmWanMbusAC 45 }

hmWanMbusACVIF14		OBJECT-TYPE
			SYNTAX	INTEGER
			MAX-ACCESS	read-only
			STATUS	current
			::= { hmWanMbusAC 46 }

hmWanMbusACValue14		OBJECT-TYPE
			SYNTAX	INTEGER
			MAX-ACCESS	read-only
			STATUS	current
			::= { hmWanMbusAC 47 }

hmWanMbusACVIF15		OBJECT-TYPE
			SYNTAX	INTEGER
			MAX-ACCESS	read-only
			STATUS	current
			::= { hmWanMbusAC 48 }

hmWanMbusACValue15		OBJECT-TYPE
			SYNTAX	INTEGER
			MAX-ACCESS	read-only
			STATUS	current
			::= { hmWanMbusAC 49 }

hmWanMbusACVIF16		OBJECT-TYPE
			SYNTAX	INTEGER
			MAX-ACCESS	read-only
			STATUS	current
			::= { hmWanMbusAC 50 }

hmWanMbusACValue16		OBJECT-TYPE
			SYNTAX	INTEGER
			MAX-ACCESS	read-only
			STATUS	current
			::= { hmWanMbusAC 51 }

hmWanMbusACVIF17		OBJECT-TYPE
			SYNTAX	INTEGER
			MAX-ACCESS	read-only
			STATUS	current
			::= { hmWanMbusAC 52 }

hmWanMbusACValue17		OBJECT-TYPE
			SYNTAX	INTEGER
			MAX-ACCESS	read-only
			STATUS	current
			::= { hmWanMbusAC 53 }

hmWanMbusACVIF18		OBJECT-TYPE
			SYNTAX	INTEGER
			MAX-ACCESS	read-only
			STATUS	current
			::= { hmWanMbusAC 54 }

hmWanMbusACValue18		OBJECT-TYPE
			SYNTAX	INTEGER
			MAX-ACCESS	read-only
			STATUS	current
			::= { hmWanMbusAC 55 }

hmWanMbusACVIF19		OBJECT-TYPE
			SYNTAX	INTEGER
			MAX-ACCESS	read-only
			STATUS	current
			::= { hmWanMbusAC 56 }

hmWanMbusACValue19		OBJECT-TYPE
			SYNTAX	INTEGER
			MAX-ACCESS	read-only
			STATUS	current
			::= { hmWanMbusAC 57 }

hmWanMbusACVIF1A		OBJECT-TYPE
			SYNTAX	INTEGER
			MAX-ACCESS	read-only
			STATUS	current
			::= { hmWanMbusAC 58 }

hmWanMbusACValue1A		OBJECT-TYPE
			SYNTAX	INTEGER
			MAX-ACCESS	read-only
			STATUS	current
			::= { hmWanMbusAC 59 }

hmWanMbusACVIF1B		OBJECT-TYPE
			SYNTAX	INTEGER
			MAX-ACCESS	read-only
			STATUS	current
			::= { hmWanMbusAC 60 }

hmWanMbusACValue1B		OBJECT-TYPE
			SYNTAX	INTEGER
			MAX-ACCESS	read-only
			STATUS	current
			::= { hmWanMbusAC 61 }

hmWanMbusACVIF1C		OBJECT-TYPE
			SYNTAX	INTEGER
			MAX-ACCESS	read-only
			STATUS	current
			::= { hmWanMbusAC 62 }

hmWanMbusACValue1C		OBJECT-TYPE
			SYNTAX	INTEGER
			MAX-ACCESS	read-only
			STATUS	current
			::= { hmWanMbusAC 63 }

hmWanMbusACVIF1D		OBJECT-TYPE
			SYNTAX	INTEGER
			MAX-ACCESS	read-only
			STATUS	current
			::= { hmWanMbusAC 64 }

hmWanMbusACValue1D		OBJECT-TYPE
			SYNTAX	INTEGER
			MAX-ACCESS	read-only
			STATUS	current
			::= { hmWanMbusAC 65 }

hmWanMbusACVIF1E		OBJECT-TYPE
			SYNTAX	INTEGER
			MAX-ACCESS	read-only
			STATUS	current
			::= { hmWanMbusAC 66 }

hmWanMbusACValue1E		OBJECT-TYPE
			SYNTAX	INTEGER
			MAX-ACCESS	read-only
			STATUS	current
			::= { hmWanMbusAC 67 }

hmWanMbusACVIF1F		OBJECT-TYPE
			SYNTAX	INTEGER
			MAX-ACCESS	read-only
			STATUS	current
			::= { hmWanMbusAC 68 }

hmWanMbusACValue1F		OBJECT-TYPE
			SYNTAX	INTEGER
			MAX-ACCESS	read-only
			STATUS	current
			::= { hmWanMbusAC 69 }

hmWanMbusACVIF20		OBJECT-TYPE
			SYNTAX	INTEGER
			MAX-ACCESS	read-only
			STATUS	current
			::= { hmWanMbusAC 70 }

hmWanMbusACValue20		OBJECT-TYPE
			SYNTAX	INTEGER
			MAX-ACCESS	read-only
			STATUS	current
			::= { hmWanMbusAC 71 }

hmWanMbusACVIF21		OBJECT-TYPE
			SYNTAX	INTEGER
			MAX-ACCESS	read-only
			STATUS	current
			::= { hmWanMbusAC 72 }

hmWanMbusACValue21		OBJECT-TYPE
			SYNTAX	INTEGER
			MAX-ACCESS	read-only
			STATUS	current
			::= { hmWanMbusAC 73 }

hmWanMbusACVIF22		OBJECT-TYPE
			SYNTAX	INTEGER
			MAX-ACCESS	read-only
			STATUS	current
			::= { hmWanMbusAC 74 }

hmWanMbusACValue22		OBJECT-TYPE
			SYNTAX	INTEGER
			MAX-ACCESS	read-only
			STATUS	current
			::= { hmWanMbusAC 75 }

hmWanMbusACVIF23		OBJECT-TYPE
			SYNTAX	INTEGER
			MAX-ACCESS	read-only
			STATUS	current
			::= { hmWanMbusAC 76 }

hmWanMbusACValue23		OBJECT-TYPE
			SYNTAX	INTEGER
			MAX-ACCESS	read-only
			STATUS	current
			::= { hmWanMbusAC 77 }

hmWanMbusACVIF24		OBJECT-TYPE
			SYNTAX	INTEGER
			MAX-ACCESS	read-only
			STATUS	current
			::= { hmWanMbusAC 78 }

hmWanMbusACValue24		OBJECT-TYPE
			SYNTAX	INTEGER
			MAX-ACCESS	read-only
			STATUS	current
			::= { hmWanMbusAC 79 }

hmWanMbusACVIF25		OBJECT-TYPE
			SYNTAX	INTEGER
			MAX-ACCESS	read-only
			STATUS	current
			::= { hmWanMbusAC 80 }

hmWanMbusACValue25		OBJECT-TYPE
			SYNTAX	INTEGER
			MAX-ACCESS	read-only
			STATUS	current
			::= { hmWanMbusAC 81 }

hmWanMbusACVIF26		OBJECT-TYPE
			SYNTAX	INTEGER
			MAX-ACCESS	read-only
			STATUS	current
			::= { hmWanMbusAC 82 }

hmWanMbusACValue26		OBJECT-TYPE
			SYNTAX	INTEGER
			MAX-ACCESS	read-only
			STATUS	current
			::= { hmWanMbusAC 83 }

hmWanMbusACVIF27		OBJECT-TYPE
			SYNTAX	INTEGER
			MAX-ACCESS	read-only
			STATUS	current
			::= { hmWanMbusAC 84 }

hmWanMbusACValue27		OBJECT-TYPE
			SYNTAX	INTEGER
			MAX-ACCESS	read-only
			STATUS	current
			::= { hmWanMbusAC 85 }

hmWanMbusACVIF28		OBJECT-TYPE
			SYNTAX	INTEGER
			MAX-ACCESS	read-only
			STATUS	current
			::= { hmWanMbusAC 86 }

hmWanMbusACValue28		OBJECT-TYPE
			SYNTAX	INTEGER
			MAX-ACCESS	read-only
			STATUS	current
			::= { hmWanMbusAC 87 }

hmWanMbusACVIF29		OBJECT-TYPE
			SYNTAX	INTEGER
			MAX-ACCESS	read-only
			STATUS	current
			::= { hmWanMbusAC 88 }

hmWanMbusACValue29		OBJECT-TYPE
			SYNTAX	INTEGER
			MAX-ACCESS	read-only
			STATUS	current
			::= { hmWanMbusAC 89 }

hmWanMbusACVIF2A		OBJECT-TYPE
			SYNTAX	INTEGER
			MAX-ACCESS	read-only
			STATUS	current
			::= { hmWanMbusAC 90 }

hmWanMbusACValue2A		OBJECT-TYPE
			SYNTAX	INTEGER
			MAX-ACCESS	read-only
			STATUS	current
			::= { hmWanMbusAC 91 }

hmWanMbusACVIF2B		OBJECT-TYPE
			SYNTAX	INTEGER
			MAX-ACCESS	read-only
			STATUS	current
			::= { hmWanMbusAC 92 }

hmWanMbusACValue2B		OBJECT-TYPE
			SYNTAX	INTEGER
			MAX-ACCESS	read-only
			STATUS	current
			::= { hmWanMbusAC 93 }

hmWanMbusACVIF2C		OBJECT-TYPE
			SYNTAX	INTEGER
			MAX-ACCESS	read-only
			STATUS	current
			::= { hmWanMbusAC 94 }

hmWanMbusACValue2C		OBJECT-TYPE
			SYNTAX	INTEGER
			MAX-ACCESS	read-only
			STATUS	current
			::= { hmWanMbusAC 95 }

hmWanMbusACVIF2D		OBJECT-TYPE
			SYNTAX	INTEGER
			MAX-ACCESS	read-only
			STATUS	current
			::= { hmWanMbusAC 96 }

hmWanMbusACValue2D		OBJECT-TYPE
			SYNTAX	INTEGER
			MAX-ACCESS	read-only
			STATUS	current
			::= { hmWanMbusAC 97 }

hmWanMbusACVIF2E		OBJECT-TYPE
			SYNTAX	INTEGER
			MAX-ACCESS	read-only
			STATUS	current
			::= { hmWanMbusAC 98 }

hmWanMbusACValue2E		OBJECT-TYPE
			SYNTAX	INTEGER
			MAX-ACCESS	read-only
			STATUS	current
			::= { hmWanMbusAC 99 }

hmWanMbusACVIF2F		OBJECT-TYPE
			SYNTAX	INTEGER
			MAX-ACCESS	read-only
			STATUS	current
			::= { hmWanMbusAC 100 }

hmWanMbusACValue2F		OBJECT-TYPE
			SYNTAX	INTEGER
			MAX-ACCESS	read-only
			STATUS	current
			::= { hmWanMbusAC 101 }

hmWanMbusAD			OBJECT IDENTIFIER ::= { hmWanMbus 173 }

hmWanMbusADIdNumber		OBJECT-TYPE
			SYNTAX	Gauge32
			MAX-ACCESS	read-only
			STATUS	current
			::= { hmWanMbusAD 1 }

hmWanMbusADManufacturer	OBJECT-TYPE
			SYNTAX	Gauge32
			MAX-ACCESS	read-only
			STATUS	current
			::= { hmWanMbusAD 2 }

hmWanMbusADVersion		OBJECT-TYPE
			SYNTAX	Gauge32
			MAX-ACCESS	read-only
			STATUS	current
			::= { hmWanMbusAD 3 }

hmWanMbusADMedium		OBJECT-TYPE
			SYNTAX	Gauge32
			MAX-ACCESS	read-only
			STATUS	current
			::= { hmWanMbusAD 4 }

hmWanMbusADStatus		OBJECT-TYPE
			SYNTAX	Gauge32
			MAX-ACCESS	read-only
			STATUS	current
			::= { hmWanMbusAD 5 }

hmWanMbusADVIF00		OBJECT-TYPE
			SYNTAX	INTEGER
			MAX-ACCESS	read-only
			STATUS	current
			::= { hmWanMbusAD 6 }

hmWanMbusADValue00		OBJECT-TYPE
			SYNTAX	INTEGER
			MAX-ACCESS	read-only
			STATUS	current
			::= { hmWanMbusAD 7 }

hmWanMbusADVIF01		OBJECT-TYPE
			SYNTAX	INTEGER
			MAX-ACCESS	read-only
			STATUS	current
			::= { hmWanMbusAD 8 }

hmWanMbusADValue01		OBJECT-TYPE
			SYNTAX	INTEGER
			MAX-ACCESS	read-only
			STATUS	current
			::= { hmWanMbusAD 9 }

hmWanMbusADVIF02		OBJECT-TYPE
			SYNTAX	INTEGER
			MAX-ACCESS	read-only
			STATUS	current
			::= { hmWanMbusAD 10 }

hmWanMbusADValue02		OBJECT-TYPE
			SYNTAX	INTEGER
			MAX-ACCESS	read-only
			STATUS	current
			::= { hmWanMbusAD 11 }

hmWanMbusADVIF03		OBJECT-TYPE
			SYNTAX	INTEGER
			MAX-ACCESS	read-only
			STATUS	current
			::= { hmWanMbusAD 12 }

hmWanMbusADValue03		OBJECT-TYPE
			SYNTAX	INTEGER
			MAX-ACCESS	read-only
			STATUS	current
			::= { hmWanMbusAD 13 }

hmWanMbusADVIF04		OBJECT-TYPE
			SYNTAX	INTEGER
			MAX-ACCESS	read-only
			STATUS	current
			::= { hmWanMbusAD 14 }

hmWanMbusADValue04		OBJECT-TYPE
			SYNTAX	INTEGER
			MAX-ACCESS	read-only
			STATUS	current
			::= { hmWanMbusAD 15 }

hmWanMbusADVIF05		OBJECT-TYPE
			SYNTAX	INTEGER
			MAX-ACCESS	read-only
			STATUS	current
			::= { hmWanMbusAD 16 }

hmWanMbusADValue05		OBJECT-TYPE
			SYNTAX	INTEGER
			MAX-ACCESS	read-only
			STATUS	current
			::= { hmWanMbusAD 17 }

hmWanMbusADVIF06		OBJECT-TYPE
			SYNTAX	INTEGER
			MAX-ACCESS	read-only
			STATUS	current
			::= { hmWanMbusAD 18 }

hmWanMbusADValue06		OBJECT-TYPE
			SYNTAX	INTEGER
			MAX-ACCESS	read-only
			STATUS	current
			::= { hmWanMbusAD 19 }

hmWanMbusADVIF07		OBJECT-TYPE
			SYNTAX	INTEGER
			MAX-ACCESS	read-only
			STATUS	current
			::= { hmWanMbusAD 20 }

hmWanMbusADValue07		OBJECT-TYPE
			SYNTAX	INTEGER
			MAX-ACCESS	read-only
			STATUS	current
			::= { hmWanMbusAD 21 }

hmWanMbusADVIF08		OBJECT-TYPE
			SYNTAX	INTEGER
			MAX-ACCESS	read-only
			STATUS	current
			::= { hmWanMbusAD 22 }

hmWanMbusADValue08		OBJECT-TYPE
			SYNTAX	INTEGER
			MAX-ACCESS	read-only
			STATUS	current
			::= { hmWanMbusAD 23 }

hmWanMbusADVIF09		OBJECT-TYPE
			SYNTAX	INTEGER
			MAX-ACCESS	read-only
			STATUS	current
			::= { hmWanMbusAD 24 }

hmWanMbusADValue09		OBJECT-TYPE
			SYNTAX	INTEGER
			MAX-ACCESS	read-only
			STATUS	current
			::= { hmWanMbusAD 25 }

hmWanMbusADVIF0A		OBJECT-TYPE
			SYNTAX	INTEGER
			MAX-ACCESS	read-only
			STATUS	current
			::= { hmWanMbusAD 26 }

hmWanMbusADValue0A		OBJECT-TYPE
			SYNTAX	INTEGER
			MAX-ACCESS	read-only
			STATUS	current
			::= { hmWanMbusAD 27 }

hmWanMbusADVIF0B		OBJECT-TYPE
			SYNTAX	INTEGER
			MAX-ACCESS	read-only
			STATUS	current
			::= { hmWanMbusAD 28 }

hmWanMbusADValue0B		OBJECT-TYPE
			SYNTAX	INTEGER
			MAX-ACCESS	read-only
			STATUS	current
			::= { hmWanMbusAD 29 }

hmWanMbusADVIF0C		OBJECT-TYPE
			SYNTAX	INTEGER
			MAX-ACCESS	read-only
			STATUS	current
			::= { hmWanMbusAD 30 }

hmWanMbusADValue0C		OBJECT-TYPE
			SYNTAX	INTEGER
			MAX-ACCESS	read-only
			STATUS	current
			::= { hmWanMbusAD 31 }

hmWanMbusADVIF0D		OBJECT-TYPE
			SYNTAX	INTEGER
			MAX-ACCESS	read-only
			STATUS	current
			::= { hmWanMbusAD 32 }

hmWanMbusADValue0D		OBJECT-TYPE
			SYNTAX	INTEGER
			MAX-ACCESS	read-only
			STATUS	current
			::= { hmWanMbusAD 33 }

hmWanMbusADVIF0E		OBJECT-TYPE
			SYNTAX	INTEGER
			MAX-ACCESS	read-only
			STATUS	current
			::= { hmWanMbusAD 34 }

hmWanMbusADValue0E		OBJECT-TYPE
			SYNTAX	INTEGER
			MAX-ACCESS	read-only
			STATUS	current
			::= { hmWanMbusAD 35 }

hmWanMbusADVIF0F		OBJECT-TYPE
			SYNTAX	INTEGER
			MAX-ACCESS	read-only
			STATUS	current
			::= { hmWanMbusAD 36 }

hmWanMbusADValue0F		OBJECT-TYPE
			SYNTAX	INTEGER
			MAX-ACCESS	read-only
			STATUS	current
			::= { hmWanMbusAD 37 }

hmWanMbusADVIF10		OBJECT-TYPE
			SYNTAX	INTEGER
			MAX-ACCESS	read-only
			STATUS	current
			::= { hmWanMbusAD 38 }

hmWanMbusADValue10		OBJECT-TYPE
			SYNTAX	INTEGER
			MAX-ACCESS	read-only
			STATUS	current
			::= { hmWanMbusAD 39 }

hmWanMbusADVIF11		OBJECT-TYPE
			SYNTAX	INTEGER
			MAX-ACCESS	read-only
			STATUS	current
			::= { hmWanMbusAD 40 }

hmWanMbusADValue11		OBJECT-TYPE
			SYNTAX	INTEGER
			MAX-ACCESS	read-only
			STATUS	current
			::= { hmWanMbusAD 41 }

hmWanMbusADVIF12		OBJECT-TYPE
			SYNTAX	INTEGER
			MAX-ACCESS	read-only
			STATUS	current
			::= { hmWanMbusAD 42 }

hmWanMbusADValue12		OBJECT-TYPE
			SYNTAX	INTEGER
			MAX-ACCESS	read-only
			STATUS	current
			::= { hmWanMbusAD 43 }

hmWanMbusADVIF13		OBJECT-TYPE
			SYNTAX	INTEGER
			MAX-ACCESS	read-only
			STATUS	current
			::= { hmWanMbusAD 44 }

hmWanMbusADValue13		OBJECT-TYPE
			SYNTAX	INTEGER
			MAX-ACCESS	read-only
			STATUS	current
			::= { hmWanMbusAD 45 }

hmWanMbusADVIF14		OBJECT-TYPE
			SYNTAX	INTEGER
			MAX-ACCESS	read-only
			STATUS	current
			::= { hmWanMbusAD 46 }

hmWanMbusADValue14		OBJECT-TYPE
			SYNTAX	INTEGER
			MAX-ACCESS	read-only
			STATUS	current
			::= { hmWanMbusAD 47 }

hmWanMbusADVIF15		OBJECT-TYPE
			SYNTAX	INTEGER
			MAX-ACCESS	read-only
			STATUS	current
			::= { hmWanMbusAD 48 }

hmWanMbusADValue15		OBJECT-TYPE
			SYNTAX	INTEGER
			MAX-ACCESS	read-only
			STATUS	current
			::= { hmWanMbusAD 49 }

hmWanMbusADVIF16		OBJECT-TYPE
			SYNTAX	INTEGER
			MAX-ACCESS	read-only
			STATUS	current
			::= { hmWanMbusAD 50 }

hmWanMbusADValue16		OBJECT-TYPE
			SYNTAX	INTEGER
			MAX-ACCESS	read-only
			STATUS	current
			::= { hmWanMbusAD 51 }

hmWanMbusADVIF17		OBJECT-TYPE
			SYNTAX	INTEGER
			MAX-ACCESS	read-only
			STATUS	current
			::= { hmWanMbusAD 52 }

hmWanMbusADValue17		OBJECT-TYPE
			SYNTAX	INTEGER
			MAX-ACCESS	read-only
			STATUS	current
			::= { hmWanMbusAD 53 }

hmWanMbusADVIF18		OBJECT-TYPE
			SYNTAX	INTEGER
			MAX-ACCESS	read-only
			STATUS	current
			::= { hmWanMbusAD 54 }

hmWanMbusADValue18		OBJECT-TYPE
			SYNTAX	INTEGER
			MAX-ACCESS	read-only
			STATUS	current
			::= { hmWanMbusAD 55 }

hmWanMbusADVIF19		OBJECT-TYPE
			SYNTAX	INTEGER
			MAX-ACCESS	read-only
			STATUS	current
			::= { hmWanMbusAD 56 }

hmWanMbusADValue19		OBJECT-TYPE
			SYNTAX	INTEGER
			MAX-ACCESS	read-only
			STATUS	current
			::= { hmWanMbusAD 57 }

hmWanMbusADVIF1A		OBJECT-TYPE
			SYNTAX	INTEGER
			MAX-ACCESS	read-only
			STATUS	current
			::= { hmWanMbusAD 58 }

hmWanMbusADValue1A		OBJECT-TYPE
			SYNTAX	INTEGER
			MAX-ACCESS	read-only
			STATUS	current
			::= { hmWanMbusAD 59 }

hmWanMbusADVIF1B		OBJECT-TYPE
			SYNTAX	INTEGER
			MAX-ACCESS	read-only
			STATUS	current
			::= { hmWanMbusAD 60 }

hmWanMbusADValue1B		OBJECT-TYPE
			SYNTAX	INTEGER
			MAX-ACCESS	read-only
			STATUS	current
			::= { hmWanMbusAD 61 }

hmWanMbusADVIF1C		OBJECT-TYPE
			SYNTAX	INTEGER
			MAX-ACCESS	read-only
			STATUS	current
			::= { hmWanMbusAD 62 }

hmWanMbusADValue1C		OBJECT-TYPE
			SYNTAX	INTEGER
			MAX-ACCESS	read-only
			STATUS	current
			::= { hmWanMbusAD 63 }

hmWanMbusADVIF1D		OBJECT-TYPE
			SYNTAX	INTEGER
			MAX-ACCESS	read-only
			STATUS	current
			::= { hmWanMbusAD 64 }

hmWanMbusADValue1D		OBJECT-TYPE
			SYNTAX	INTEGER
			MAX-ACCESS	read-only
			STATUS	current
			::= { hmWanMbusAD 65 }

hmWanMbusADVIF1E		OBJECT-TYPE
			SYNTAX	INTEGER
			MAX-ACCESS	read-only
			STATUS	current
			::= { hmWanMbusAD 66 }

hmWanMbusADValue1E		OBJECT-TYPE
			SYNTAX	INTEGER
			MAX-ACCESS	read-only
			STATUS	current
			::= { hmWanMbusAD 67 }

hmWanMbusADVIF1F		OBJECT-TYPE
			SYNTAX	INTEGER
			MAX-ACCESS	read-only
			STATUS	current
			::= { hmWanMbusAD 68 }

hmWanMbusADValue1F		OBJECT-TYPE
			SYNTAX	INTEGER
			MAX-ACCESS	read-only
			STATUS	current
			::= { hmWanMbusAD 69 }

hmWanMbusADVIF20		OBJECT-TYPE
			SYNTAX	INTEGER
			MAX-ACCESS	read-only
			STATUS	current
			::= { hmWanMbusAD 70 }

hmWanMbusADValue20		OBJECT-TYPE
			SYNTAX	INTEGER
			MAX-ACCESS	read-only
			STATUS	current
			::= { hmWanMbusAD 71 }

hmWanMbusADVIF21		OBJECT-TYPE
			SYNTAX	INTEGER
			MAX-ACCESS	read-only
			STATUS	current
			::= { hmWanMbusAD 72 }

hmWanMbusADValue21		OBJECT-TYPE
			SYNTAX	INTEGER
			MAX-ACCESS	read-only
			STATUS	current
			::= { hmWanMbusAD 73 }

hmWanMbusADVIF22		OBJECT-TYPE
			SYNTAX	INTEGER
			MAX-ACCESS	read-only
			STATUS	current
			::= { hmWanMbusAD 74 }

hmWanMbusADValue22		OBJECT-TYPE
			SYNTAX	INTEGER
			MAX-ACCESS	read-only
			STATUS	current
			::= { hmWanMbusAD 75 }

hmWanMbusADVIF23		OBJECT-TYPE
			SYNTAX	INTEGER
			MAX-ACCESS	read-only
			STATUS	current
			::= { hmWanMbusAD 76 }

hmWanMbusADValue23		OBJECT-TYPE
			SYNTAX	INTEGER
			MAX-ACCESS	read-only
			STATUS	current
			::= { hmWanMbusAD 77 }

hmWanMbusADVIF24		OBJECT-TYPE
			SYNTAX	INTEGER
			MAX-ACCESS	read-only
			STATUS	current
			::= { hmWanMbusAD 78 }

hmWanMbusADValue24		OBJECT-TYPE
			SYNTAX	INTEGER
			MAX-ACCESS	read-only
			STATUS	current
			::= { hmWanMbusAD 79 }

hmWanMbusADVIF25		OBJECT-TYPE
			SYNTAX	INTEGER
			MAX-ACCESS	read-only
			STATUS	current
			::= { hmWanMbusAD 80 }

hmWanMbusADValue25		OBJECT-TYPE
			SYNTAX	INTEGER
			MAX-ACCESS	read-only
			STATUS	current
			::= { hmWanMbusAD 81 }

hmWanMbusADVIF26		OBJECT-TYPE
			SYNTAX	INTEGER
			MAX-ACCESS	read-only
			STATUS	current
			::= { hmWanMbusAD 82 }

hmWanMbusADValue26		OBJECT-TYPE
			SYNTAX	INTEGER
			MAX-ACCESS	read-only
			STATUS	current
			::= { hmWanMbusAD 83 }

hmWanMbusADVIF27		OBJECT-TYPE
			SYNTAX	INTEGER
			MAX-ACCESS	read-only
			STATUS	current
			::= { hmWanMbusAD 84 }

hmWanMbusADValue27		OBJECT-TYPE
			SYNTAX	INTEGER
			MAX-ACCESS	read-only
			STATUS	current
			::= { hmWanMbusAD 85 }

hmWanMbusADVIF28		OBJECT-TYPE
			SYNTAX	INTEGER
			MAX-ACCESS	read-only
			STATUS	current
			::= { hmWanMbusAD 86 }

hmWanMbusADValue28		OBJECT-TYPE
			SYNTAX	INTEGER
			MAX-ACCESS	read-only
			STATUS	current
			::= { hmWanMbusAD 87 }

hmWanMbusADVIF29		OBJECT-TYPE
			SYNTAX	INTEGER
			MAX-ACCESS	read-only
			STATUS	current
			::= { hmWanMbusAD 88 }

hmWanMbusADValue29		OBJECT-TYPE
			SYNTAX	INTEGER
			MAX-ACCESS	read-only
			STATUS	current
			::= { hmWanMbusAD 89 }

hmWanMbusADVIF2A		OBJECT-TYPE
			SYNTAX	INTEGER
			MAX-ACCESS	read-only
			STATUS	current
			::= { hmWanMbusAD 90 }

hmWanMbusADValue2A		OBJECT-TYPE
			SYNTAX	INTEGER
			MAX-ACCESS	read-only
			STATUS	current
			::= { hmWanMbusAD 91 }

hmWanMbusADVIF2B		OBJECT-TYPE
			SYNTAX	INTEGER
			MAX-ACCESS	read-only
			STATUS	current
			::= { hmWanMbusAD 92 }

hmWanMbusADValue2B		OBJECT-TYPE
			SYNTAX	INTEGER
			MAX-ACCESS	read-only
			STATUS	current
			::= { hmWanMbusAD 93 }

hmWanMbusADVIF2C		OBJECT-TYPE
			SYNTAX	INTEGER
			MAX-ACCESS	read-only
			STATUS	current
			::= { hmWanMbusAD 94 }

hmWanMbusADValue2C		OBJECT-TYPE
			SYNTAX	INTEGER
			MAX-ACCESS	read-only
			STATUS	current
			::= { hmWanMbusAD 95 }

hmWanMbusADVIF2D		OBJECT-TYPE
			SYNTAX	INTEGER
			MAX-ACCESS	read-only
			STATUS	current
			::= { hmWanMbusAD 96 }

hmWanMbusADValue2D		OBJECT-TYPE
			SYNTAX	INTEGER
			MAX-ACCESS	read-only
			STATUS	current
			::= { hmWanMbusAD 97 }

hmWanMbusADVIF2E		OBJECT-TYPE
			SYNTAX	INTEGER
			MAX-ACCESS	read-only
			STATUS	current
			::= { hmWanMbusAD 98 }

hmWanMbusADValue2E		OBJECT-TYPE
			SYNTAX	INTEGER
			MAX-ACCESS	read-only
			STATUS	current
			::= { hmWanMbusAD 99 }

hmWanMbusADVIF2F		OBJECT-TYPE
			SYNTAX	INTEGER
			MAX-ACCESS	read-only
			STATUS	current
			::= { hmWanMbusAD 100 }

hmWanMbusADValue2F		OBJECT-TYPE
			SYNTAX	INTEGER
			MAX-ACCESS	read-only
			STATUS	current
			::= { hmWanMbusAD 101 }

hmWanMbusAE			OBJECT IDENTIFIER ::= { hmWanMbus 174 }

hmWanMbusAEIdNumber		OBJECT-TYPE
			SYNTAX	Gauge32
			MAX-ACCESS	read-only
			STATUS	current
			::= { hmWanMbusAE 1 }

hmWanMbusAEManufacturer	OBJECT-TYPE
			SYNTAX	Gauge32
			MAX-ACCESS	read-only
			STATUS	current
			::= { hmWanMbusAE 2 }

hmWanMbusAEVersion		OBJECT-TYPE
			SYNTAX	Gauge32
			MAX-ACCESS	read-only
			STATUS	current
			::= { hmWanMbusAE 3 }

hmWanMbusAEMedium		OBJECT-TYPE
			SYNTAX	Gauge32
			MAX-ACCESS	read-only
			STATUS	current
			::= { hmWanMbusAE 4 }

hmWanMbusAEStatus		OBJECT-TYPE
			SYNTAX	Gauge32
			MAX-ACCESS	read-only
			STATUS	current
			::= { hmWanMbusAE 5 }

hmWanMbusAEVIF00		OBJECT-TYPE
			SYNTAX	INTEGER
			MAX-ACCESS	read-only
			STATUS	current
			::= { hmWanMbusAE 6 }

hmWanMbusAEValue00		OBJECT-TYPE
			SYNTAX	INTEGER
			MAX-ACCESS	read-only
			STATUS	current
			::= { hmWanMbusAE 7 }

hmWanMbusAEVIF01		OBJECT-TYPE
			SYNTAX	INTEGER
			MAX-ACCESS	read-only
			STATUS	current
			::= { hmWanMbusAE 8 }

hmWanMbusAEValue01		OBJECT-TYPE
			SYNTAX	INTEGER
			MAX-ACCESS	read-only
			STATUS	current
			::= { hmWanMbusAE 9 }

hmWanMbusAEVIF02		OBJECT-TYPE
			SYNTAX	INTEGER
			MAX-ACCESS	read-only
			STATUS	current
			::= { hmWanMbusAE 10 }

hmWanMbusAEValue02		OBJECT-TYPE
			SYNTAX	INTEGER
			MAX-ACCESS	read-only
			STATUS	current
			::= { hmWanMbusAE 11 }

hmWanMbusAEVIF03		OBJECT-TYPE
			SYNTAX	INTEGER
			MAX-ACCESS	read-only
			STATUS	current
			::= { hmWanMbusAE 12 }

hmWanMbusAEValue03		OBJECT-TYPE
			SYNTAX	INTEGER
			MAX-ACCESS	read-only
			STATUS	current
			::= { hmWanMbusAE 13 }

hmWanMbusAEVIF04		OBJECT-TYPE
			SYNTAX	INTEGER
			MAX-ACCESS	read-only
			STATUS	current
			::= { hmWanMbusAE 14 }

hmWanMbusAEValue04		OBJECT-TYPE
			SYNTAX	INTEGER
			MAX-ACCESS	read-only
			STATUS	current
			::= { hmWanMbusAE 15 }

hmWanMbusAEVIF05		OBJECT-TYPE
			SYNTAX	INTEGER
			MAX-ACCESS	read-only
			STATUS	current
			::= { hmWanMbusAE 16 }

hmWanMbusAEValue05		OBJECT-TYPE
			SYNTAX	INTEGER
			MAX-ACCESS	read-only
			STATUS	current
			::= { hmWanMbusAE 17 }

hmWanMbusAEVIF06		OBJECT-TYPE
			SYNTAX	INTEGER
			MAX-ACCESS	read-only
			STATUS	current
			::= { hmWanMbusAE 18 }

hmWanMbusAEValue06		OBJECT-TYPE
			SYNTAX	INTEGER
			MAX-ACCESS	read-only
			STATUS	current
			::= { hmWanMbusAE 19 }

hmWanMbusAEVIF07		OBJECT-TYPE
			SYNTAX	INTEGER
			MAX-ACCESS	read-only
			STATUS	current
			::= { hmWanMbusAE 20 }

hmWanMbusAEValue07		OBJECT-TYPE
			SYNTAX	INTEGER
			MAX-ACCESS	read-only
			STATUS	current
			::= { hmWanMbusAE 21 }

hmWanMbusAEVIF08		OBJECT-TYPE
			SYNTAX	INTEGER
			MAX-ACCESS	read-only
			STATUS	current
			::= { hmWanMbusAE 22 }

hmWanMbusAEValue08		OBJECT-TYPE
			SYNTAX	INTEGER
			MAX-ACCESS	read-only
			STATUS	current
			::= { hmWanMbusAE 23 }

hmWanMbusAEVIF09		OBJECT-TYPE
			SYNTAX	INTEGER
			MAX-ACCESS	read-only
			STATUS	current
			::= { hmWanMbusAE 24 }

hmWanMbusAEValue09		OBJECT-TYPE
			SYNTAX	INTEGER
			MAX-ACCESS	read-only
			STATUS	current
			::= { hmWanMbusAE 25 }

hmWanMbusAEVIF0A		OBJECT-TYPE
			SYNTAX	INTEGER
			MAX-ACCESS	read-only
			STATUS	current
			::= { hmWanMbusAE 26 }

hmWanMbusAEValue0A		OBJECT-TYPE
			SYNTAX	INTEGER
			MAX-ACCESS	read-only
			STATUS	current
			::= { hmWanMbusAE 27 }

hmWanMbusAEVIF0B		OBJECT-TYPE
			SYNTAX	INTEGER
			MAX-ACCESS	read-only
			STATUS	current
			::= { hmWanMbusAE 28 }

hmWanMbusAEValue0B		OBJECT-TYPE
			SYNTAX	INTEGER
			MAX-ACCESS	read-only
			STATUS	current
			::= { hmWanMbusAE 29 }

hmWanMbusAEVIF0C		OBJECT-TYPE
			SYNTAX	INTEGER
			MAX-ACCESS	read-only
			STATUS	current
			::= { hmWanMbusAE 30 }

hmWanMbusAEValue0C		OBJECT-TYPE
			SYNTAX	INTEGER
			MAX-ACCESS	read-only
			STATUS	current
			::= { hmWanMbusAE 31 }

hmWanMbusAEVIF0D		OBJECT-TYPE
			SYNTAX	INTEGER
			MAX-ACCESS	read-only
			STATUS	current
			::= { hmWanMbusAE 32 }

hmWanMbusAEValue0D		OBJECT-TYPE
			SYNTAX	INTEGER
			MAX-ACCESS	read-only
			STATUS	current
			::= { hmWanMbusAE 33 }

hmWanMbusAEVIF0E		OBJECT-TYPE
			SYNTAX	INTEGER
			MAX-ACCESS	read-only
			STATUS	current
			::= { hmWanMbusAE 34 }

hmWanMbusAEValue0E		OBJECT-TYPE
			SYNTAX	INTEGER
			MAX-ACCESS	read-only
			STATUS	current
			::= { hmWanMbusAE 35 }

hmWanMbusAEVIF0F		OBJECT-TYPE
			SYNTAX	INTEGER
			MAX-ACCESS	read-only
			STATUS	current
			::= { hmWanMbusAE 36 }

hmWanMbusAEValue0F		OBJECT-TYPE
			SYNTAX	INTEGER
			MAX-ACCESS	read-only
			STATUS	current
			::= { hmWanMbusAE 37 }

hmWanMbusAEVIF10		OBJECT-TYPE
			SYNTAX	INTEGER
			MAX-ACCESS	read-only
			STATUS	current
			::= { hmWanMbusAE 38 }

hmWanMbusAEValue10		OBJECT-TYPE
			SYNTAX	INTEGER
			MAX-ACCESS	read-only
			STATUS	current
			::= { hmWanMbusAE 39 }

hmWanMbusAEVIF11		OBJECT-TYPE
			SYNTAX	INTEGER
			MAX-ACCESS	read-only
			STATUS	current
			::= { hmWanMbusAE 40 }

hmWanMbusAEValue11		OBJECT-TYPE
			SYNTAX	INTEGER
			MAX-ACCESS	read-only
			STATUS	current
			::= { hmWanMbusAE 41 }

hmWanMbusAEVIF12		OBJECT-TYPE
			SYNTAX	INTEGER
			MAX-ACCESS	read-only
			STATUS	current
			::= { hmWanMbusAE 42 }

hmWanMbusAEValue12		OBJECT-TYPE
			SYNTAX	INTEGER
			MAX-ACCESS	read-only
			STATUS	current
			::= { hmWanMbusAE 43 }

hmWanMbusAEVIF13		OBJECT-TYPE
			SYNTAX	INTEGER
			MAX-ACCESS	read-only
			STATUS	current
			::= { hmWanMbusAE 44 }

hmWanMbusAEValue13		OBJECT-TYPE
			SYNTAX	INTEGER
			MAX-ACCESS	read-only
			STATUS	current
			::= { hmWanMbusAE 45 }

hmWanMbusAEVIF14		OBJECT-TYPE
			SYNTAX	INTEGER
			MAX-ACCESS	read-only
			STATUS	current
			::= { hmWanMbusAE 46 }

hmWanMbusAEValue14		OBJECT-TYPE
			SYNTAX	INTEGER
			MAX-ACCESS	read-only
			STATUS	current
			::= { hmWanMbusAE 47 }

hmWanMbusAEVIF15		OBJECT-TYPE
			SYNTAX	INTEGER
			MAX-ACCESS	read-only
			STATUS	current
			::= { hmWanMbusAE 48 }

hmWanMbusAEValue15		OBJECT-TYPE
			SYNTAX	INTEGER
			MAX-ACCESS	read-only
			STATUS	current
			::= { hmWanMbusAE 49 }

hmWanMbusAEVIF16		OBJECT-TYPE
			SYNTAX	INTEGER
			MAX-ACCESS	read-only
			STATUS	current
			::= { hmWanMbusAE 50 }

hmWanMbusAEValue16		OBJECT-TYPE
			SYNTAX	INTEGER
			MAX-ACCESS	read-only
			STATUS	current
			::= { hmWanMbusAE 51 }

hmWanMbusAEVIF17		OBJECT-TYPE
			SYNTAX	INTEGER
			MAX-ACCESS	read-only
			STATUS	current
			::= { hmWanMbusAE 52 }

hmWanMbusAEValue17		OBJECT-TYPE
			SYNTAX	INTEGER
			MAX-ACCESS	read-only
			STATUS	current
			::= { hmWanMbusAE 53 }

hmWanMbusAEVIF18		OBJECT-TYPE
			SYNTAX	INTEGER
			MAX-ACCESS	read-only
			STATUS	current
			::= { hmWanMbusAE 54 }

hmWanMbusAEValue18		OBJECT-TYPE
			SYNTAX	INTEGER
			MAX-ACCESS	read-only
			STATUS	current
			::= { hmWanMbusAE 55 }

hmWanMbusAEVIF19		OBJECT-TYPE
			SYNTAX	INTEGER
			MAX-ACCESS	read-only
			STATUS	current
			::= { hmWanMbusAE 56 }

hmWanMbusAEValue19		OBJECT-TYPE
			SYNTAX	INTEGER
			MAX-ACCESS	read-only
			STATUS	current
			::= { hmWanMbusAE 57 }

hmWanMbusAEVIF1A		OBJECT-TYPE
			SYNTAX	INTEGER
			MAX-ACCESS	read-only
			STATUS	current
			::= { hmWanMbusAE 58 }

hmWanMbusAEValue1A		OBJECT-TYPE
			SYNTAX	INTEGER
			MAX-ACCESS	read-only
			STATUS	current
			::= { hmWanMbusAE 59 }

hmWanMbusAEVIF1B		OBJECT-TYPE
			SYNTAX	INTEGER
			MAX-ACCESS	read-only
			STATUS	current
			::= { hmWanMbusAE 60 }

hmWanMbusAEValue1B		OBJECT-TYPE
			SYNTAX	INTEGER
			MAX-ACCESS	read-only
			STATUS	current
			::= { hmWanMbusAE 61 }

hmWanMbusAEVIF1C		OBJECT-TYPE
			SYNTAX	INTEGER
			MAX-ACCESS	read-only
			STATUS	current
			::= { hmWanMbusAE 62 }

hmWanMbusAEValue1C		OBJECT-TYPE
			SYNTAX	INTEGER
			MAX-ACCESS	read-only
			STATUS	current
			::= { hmWanMbusAE 63 }

hmWanMbusAEVIF1D		OBJECT-TYPE
			SYNTAX	INTEGER
			MAX-ACCESS	read-only
			STATUS	current
			::= { hmWanMbusAE 64 }

hmWanMbusAEValue1D		OBJECT-TYPE
			SYNTAX	INTEGER
			MAX-ACCESS	read-only
			STATUS	current
			::= { hmWanMbusAE 65 }

hmWanMbusAEVIF1E		OBJECT-TYPE
			SYNTAX	INTEGER
			MAX-ACCESS	read-only
			STATUS	current
			::= { hmWanMbusAE 66 }

hmWanMbusAEValue1E		OBJECT-TYPE
			SYNTAX	INTEGER
			MAX-ACCESS	read-only
			STATUS	current
			::= { hmWanMbusAE 67 }

hmWanMbusAEVIF1F		OBJECT-TYPE
			SYNTAX	INTEGER
			MAX-ACCESS	read-only
			STATUS	current
			::= { hmWanMbusAE 68 }

hmWanMbusAEValue1F		OBJECT-TYPE
			SYNTAX	INTEGER
			MAX-ACCESS	read-only
			STATUS	current
			::= { hmWanMbusAE 69 }

hmWanMbusAEVIF20		OBJECT-TYPE
			SYNTAX	INTEGER
			MAX-ACCESS	read-only
			STATUS	current
			::= { hmWanMbusAE 70 }

hmWanMbusAEValue20		OBJECT-TYPE
			SYNTAX	INTEGER
			MAX-ACCESS	read-only
			STATUS	current
			::= { hmWanMbusAE 71 }

hmWanMbusAEVIF21		OBJECT-TYPE
			SYNTAX	INTEGER
			MAX-ACCESS	read-only
			STATUS	current
			::= { hmWanMbusAE 72 }

hmWanMbusAEValue21		OBJECT-TYPE
			SYNTAX	INTEGER
			MAX-ACCESS	read-only
			STATUS	current
			::= { hmWanMbusAE 73 }

hmWanMbusAEVIF22		OBJECT-TYPE
			SYNTAX	INTEGER
			MAX-ACCESS	read-only
			STATUS	current
			::= { hmWanMbusAE 74 }

hmWanMbusAEValue22		OBJECT-TYPE
			SYNTAX	INTEGER
			MAX-ACCESS	read-only
			STATUS	current
			::= { hmWanMbusAE 75 }

hmWanMbusAEVIF23		OBJECT-TYPE
			SYNTAX	INTEGER
			MAX-ACCESS	read-only
			STATUS	current
			::= { hmWanMbusAE 76 }

hmWanMbusAEValue23		OBJECT-TYPE
			SYNTAX	INTEGER
			MAX-ACCESS	read-only
			STATUS	current
			::= { hmWanMbusAE 77 }

hmWanMbusAEVIF24		OBJECT-TYPE
			SYNTAX	INTEGER
			MAX-ACCESS	read-only
			STATUS	current
			::= { hmWanMbusAE 78 }

hmWanMbusAEValue24		OBJECT-TYPE
			SYNTAX	INTEGER
			MAX-ACCESS	read-only
			STATUS	current
			::= { hmWanMbusAE 79 }

hmWanMbusAEVIF25		OBJECT-TYPE
			SYNTAX	INTEGER
			MAX-ACCESS	read-only
			STATUS	current
			::= { hmWanMbusAE 80 }

hmWanMbusAEValue25		OBJECT-TYPE
			SYNTAX	INTEGER
			MAX-ACCESS	read-only
			STATUS	current
			::= { hmWanMbusAE 81 }

hmWanMbusAEVIF26		OBJECT-TYPE
			SYNTAX	INTEGER
			MAX-ACCESS	read-only
			STATUS	current
			::= { hmWanMbusAE 82 }

hmWanMbusAEValue26		OBJECT-TYPE
			SYNTAX	INTEGER
			MAX-ACCESS	read-only
			STATUS	current
			::= { hmWanMbusAE 83 }

hmWanMbusAEVIF27		OBJECT-TYPE
			SYNTAX	INTEGER
			MAX-ACCESS	read-only
			STATUS	current
			::= { hmWanMbusAE 84 }

hmWanMbusAEValue27		OBJECT-TYPE
			SYNTAX	INTEGER
			MAX-ACCESS	read-only
			STATUS	current
			::= { hmWanMbusAE 85 }

hmWanMbusAEVIF28		OBJECT-TYPE
			SYNTAX	INTEGER
			MAX-ACCESS	read-only
			STATUS	current
			::= { hmWanMbusAE 86 }

hmWanMbusAEValue28		OBJECT-TYPE
			SYNTAX	INTEGER
			MAX-ACCESS	read-only
			STATUS	current
			::= { hmWanMbusAE 87 }

hmWanMbusAEVIF29		OBJECT-TYPE
			SYNTAX	INTEGER
			MAX-ACCESS	read-only
			STATUS	current
			::= { hmWanMbusAE 88 }

hmWanMbusAEValue29		OBJECT-TYPE
			SYNTAX	INTEGER
			MAX-ACCESS	read-only
			STATUS	current
			::= { hmWanMbusAE 89 }

hmWanMbusAEVIF2A		OBJECT-TYPE
			SYNTAX	INTEGER
			MAX-ACCESS	read-only
			STATUS	current
			::= { hmWanMbusAE 90 }

hmWanMbusAEValue2A		OBJECT-TYPE
			SYNTAX	INTEGER
			MAX-ACCESS	read-only
			STATUS	current
			::= { hmWanMbusAE 91 }

hmWanMbusAEVIF2B		OBJECT-TYPE
			SYNTAX	INTEGER
			MAX-ACCESS	read-only
			STATUS	current
			::= { hmWanMbusAE 92 }

hmWanMbusAEValue2B		OBJECT-TYPE
			SYNTAX	INTEGER
			MAX-ACCESS	read-only
			STATUS	current
			::= { hmWanMbusAE 93 }

hmWanMbusAEVIF2C		OBJECT-TYPE
			SYNTAX	INTEGER
			MAX-ACCESS	read-only
			STATUS	current
			::= { hmWanMbusAE 94 }

hmWanMbusAEValue2C		OBJECT-TYPE
			SYNTAX	INTEGER
			MAX-ACCESS	read-only
			STATUS	current
			::= { hmWanMbusAE 95 }

hmWanMbusAEVIF2D		OBJECT-TYPE
			SYNTAX	INTEGER
			MAX-ACCESS	read-only
			STATUS	current
			::= { hmWanMbusAE 96 }

hmWanMbusAEValue2D		OBJECT-TYPE
			SYNTAX	INTEGER
			MAX-ACCESS	read-only
			STATUS	current
			::= { hmWanMbusAE 97 }

hmWanMbusAEVIF2E		OBJECT-TYPE
			SYNTAX	INTEGER
			MAX-ACCESS	read-only
			STATUS	current
			::= { hmWanMbusAE 98 }

hmWanMbusAEValue2E		OBJECT-TYPE
			SYNTAX	INTEGER
			MAX-ACCESS	read-only
			STATUS	current
			::= { hmWanMbusAE 99 }

hmWanMbusAEVIF2F		OBJECT-TYPE
			SYNTAX	INTEGER
			MAX-ACCESS	read-only
			STATUS	current
			::= { hmWanMbusAE 100 }

hmWanMbusAEValue2F		OBJECT-TYPE
			SYNTAX	INTEGER
			MAX-ACCESS	read-only
			STATUS	current
			::= { hmWanMbusAE 101 }

hmWanMbusAF			OBJECT IDENTIFIER ::= { hmWanMbus 175 }

hmWanMbusAFIdNumber		OBJECT-TYPE
			SYNTAX	Gauge32
			MAX-ACCESS	read-only
			STATUS	current
			::= { hmWanMbusAF 1 }

hmWanMbusAFManufacturer	OBJECT-TYPE
			SYNTAX	Gauge32
			MAX-ACCESS	read-only
			STATUS	current
			::= { hmWanMbusAF 2 }

hmWanMbusAFVersion		OBJECT-TYPE
			SYNTAX	Gauge32
			MAX-ACCESS	read-only
			STATUS	current
			::= { hmWanMbusAF 3 }

hmWanMbusAFMedium		OBJECT-TYPE
			SYNTAX	Gauge32
			MAX-ACCESS	read-only
			STATUS	current
			::= { hmWanMbusAF 4 }

hmWanMbusAFStatus		OBJECT-TYPE
			SYNTAX	Gauge32
			MAX-ACCESS	read-only
			STATUS	current
			::= { hmWanMbusAF 5 }

hmWanMbusAFVIF00		OBJECT-TYPE
			SYNTAX	INTEGER
			MAX-ACCESS	read-only
			STATUS	current
			::= { hmWanMbusAF 6 }

hmWanMbusAFValue00		OBJECT-TYPE
			SYNTAX	INTEGER
			MAX-ACCESS	read-only
			STATUS	current
			::= { hmWanMbusAF 7 }

hmWanMbusAFVIF01		OBJECT-TYPE
			SYNTAX	INTEGER
			MAX-ACCESS	read-only
			STATUS	current
			::= { hmWanMbusAF 8 }

hmWanMbusAFValue01		OBJECT-TYPE
			SYNTAX	INTEGER
			MAX-ACCESS	read-only
			STATUS	current
			::= { hmWanMbusAF 9 }

hmWanMbusAFVIF02		OBJECT-TYPE
			SYNTAX	INTEGER
			MAX-ACCESS	read-only
			STATUS	current
			::= { hmWanMbusAF 10 }

hmWanMbusAFValue02		OBJECT-TYPE
			SYNTAX	INTEGER
			MAX-ACCESS	read-only
			STATUS	current
			::= { hmWanMbusAF 11 }

hmWanMbusAFVIF03		OBJECT-TYPE
			SYNTAX	INTEGER
			MAX-ACCESS	read-only
			STATUS	current
			::= { hmWanMbusAF 12 }

hmWanMbusAFValue03		OBJECT-TYPE
			SYNTAX	INTEGER
			MAX-ACCESS	read-only
			STATUS	current
			::= { hmWanMbusAF 13 }

hmWanMbusAFVIF04		OBJECT-TYPE
			SYNTAX	INTEGER
			MAX-ACCESS	read-only
			STATUS	current
			::= { hmWanMbusAF 14 }

hmWanMbusAFValue04		OBJECT-TYPE
			SYNTAX	INTEGER
			MAX-ACCESS	read-only
			STATUS	current
			::= { hmWanMbusAF 15 }

hmWanMbusAFVIF05		OBJECT-TYPE
			SYNTAX	INTEGER
			MAX-ACCESS	read-only
			STATUS	current
			::= { hmWanMbusAF 16 }

hmWanMbusAFValue05		OBJECT-TYPE
			SYNTAX	INTEGER
			MAX-ACCESS	read-only
			STATUS	current
			::= { hmWanMbusAF 17 }

hmWanMbusAFVIF06		OBJECT-TYPE
			SYNTAX	INTEGER
			MAX-ACCESS	read-only
			STATUS	current
			::= { hmWanMbusAF 18 }

hmWanMbusAFValue06		OBJECT-TYPE
			SYNTAX	INTEGER
			MAX-ACCESS	read-only
			STATUS	current
			::= { hmWanMbusAF 19 }

hmWanMbusAFVIF07		OBJECT-TYPE
			SYNTAX	INTEGER
			MAX-ACCESS	read-only
			STATUS	current
			::= { hmWanMbusAF 20 }

hmWanMbusAFValue07		OBJECT-TYPE
			SYNTAX	INTEGER
			MAX-ACCESS	read-only
			STATUS	current
			::= { hmWanMbusAF 21 }

hmWanMbusAFVIF08		OBJECT-TYPE
			SYNTAX	INTEGER
			MAX-ACCESS	read-only
			STATUS	current
			::= { hmWanMbusAF 22 }

hmWanMbusAFValue08		OBJECT-TYPE
			SYNTAX	INTEGER
			MAX-ACCESS	read-only
			STATUS	current
			::= { hmWanMbusAF 23 }

hmWanMbusAFVIF09		OBJECT-TYPE
			SYNTAX	INTEGER
			MAX-ACCESS	read-only
			STATUS	current
			::= { hmWanMbusAF 24 }

hmWanMbusAFValue09		OBJECT-TYPE
			SYNTAX	INTEGER
			MAX-ACCESS	read-only
			STATUS	current
			::= { hmWanMbusAF 25 }

hmWanMbusAFVIF0A		OBJECT-TYPE
			SYNTAX	INTEGER
			MAX-ACCESS	read-only
			STATUS	current
			::= { hmWanMbusAF 26 }

hmWanMbusAFValue0A		OBJECT-TYPE
			SYNTAX	INTEGER
			MAX-ACCESS	read-only
			STATUS	current
			::= { hmWanMbusAF 27 }

hmWanMbusAFVIF0B		OBJECT-TYPE
			SYNTAX	INTEGER
			MAX-ACCESS	read-only
			STATUS	current
			::= { hmWanMbusAF 28 }

hmWanMbusAFValue0B		OBJECT-TYPE
			SYNTAX	INTEGER
			MAX-ACCESS	read-only
			STATUS	current
			::= { hmWanMbusAF 29 }

hmWanMbusAFVIF0C		OBJECT-TYPE
			SYNTAX	INTEGER
			MAX-ACCESS	read-only
			STATUS	current
			::= { hmWanMbusAF 30 }

hmWanMbusAFValue0C		OBJECT-TYPE
			SYNTAX	INTEGER
			MAX-ACCESS	read-only
			STATUS	current
			::= { hmWanMbusAF 31 }

hmWanMbusAFVIF0D		OBJECT-TYPE
			SYNTAX	INTEGER
			MAX-ACCESS	read-only
			STATUS	current
			::= { hmWanMbusAF 32 }

hmWanMbusAFValue0D		OBJECT-TYPE
			SYNTAX	INTEGER
			MAX-ACCESS	read-only
			STATUS	current
			::= { hmWanMbusAF 33 }

hmWanMbusAFVIF0E		OBJECT-TYPE
			SYNTAX	INTEGER
			MAX-ACCESS	read-only
			STATUS	current
			::= { hmWanMbusAF 34 }

hmWanMbusAFValue0E		OBJECT-TYPE
			SYNTAX	INTEGER
			MAX-ACCESS	read-only
			STATUS	current
			::= { hmWanMbusAF 35 }

hmWanMbusAFVIF0F		OBJECT-TYPE
			SYNTAX	INTEGER
			MAX-ACCESS	read-only
			STATUS	current
			::= { hmWanMbusAF 36 }

hmWanMbusAFValue0F		OBJECT-TYPE
			SYNTAX	INTEGER
			MAX-ACCESS	read-only
			STATUS	current
			::= { hmWanMbusAF 37 }

hmWanMbusAFVIF10		OBJECT-TYPE
			SYNTAX	INTEGER
			MAX-ACCESS	read-only
			STATUS	current
			::= { hmWanMbusAF 38 }

hmWanMbusAFValue10		OBJECT-TYPE
			SYNTAX	INTEGER
			MAX-ACCESS	read-only
			STATUS	current
			::= { hmWanMbusAF 39 }

hmWanMbusAFVIF11		OBJECT-TYPE
			SYNTAX	INTEGER
			MAX-ACCESS	read-only
			STATUS	current
			::= { hmWanMbusAF 40 }

hmWanMbusAFValue11		OBJECT-TYPE
			SYNTAX	INTEGER
			MAX-ACCESS	read-only
			STATUS	current
			::= { hmWanMbusAF 41 }

hmWanMbusAFVIF12		OBJECT-TYPE
			SYNTAX	INTEGER
			MAX-ACCESS	read-only
			STATUS	current
			::= { hmWanMbusAF 42 }

hmWanMbusAFValue12		OBJECT-TYPE
			SYNTAX	INTEGER
			MAX-ACCESS	read-only
			STATUS	current
			::= { hmWanMbusAF 43 }

hmWanMbusAFVIF13		OBJECT-TYPE
			SYNTAX	INTEGER
			MAX-ACCESS	read-only
			STATUS	current
			::= { hmWanMbusAF 44 }

hmWanMbusAFValue13		OBJECT-TYPE
			SYNTAX	INTEGER
			MAX-ACCESS	read-only
			STATUS	current
			::= { hmWanMbusAF 45 }

hmWanMbusAFVIF14		OBJECT-TYPE
			SYNTAX	INTEGER
			MAX-ACCESS	read-only
			STATUS	current
			::= { hmWanMbusAF 46 }

hmWanMbusAFValue14		OBJECT-TYPE
			SYNTAX	INTEGER
			MAX-ACCESS	read-only
			STATUS	current
			::= { hmWanMbusAF 47 }

hmWanMbusAFVIF15		OBJECT-TYPE
			SYNTAX	INTEGER
			MAX-ACCESS	read-only
			STATUS	current
			::= { hmWanMbusAF 48 }

hmWanMbusAFValue15		OBJECT-TYPE
			SYNTAX	INTEGER
			MAX-ACCESS	read-only
			STATUS	current
			::= { hmWanMbusAF 49 }

hmWanMbusAFVIF16		OBJECT-TYPE
			SYNTAX	INTEGER
			MAX-ACCESS	read-only
			STATUS	current
			::= { hmWanMbusAF 50 }

hmWanMbusAFValue16		OBJECT-TYPE
			SYNTAX	INTEGER
			MAX-ACCESS	read-only
			STATUS	current
			::= { hmWanMbusAF 51 }

hmWanMbusAFVIF17		OBJECT-TYPE
			SYNTAX	INTEGER
			MAX-ACCESS	read-only
			STATUS	current
			::= { hmWanMbusAF 52 }

hmWanMbusAFValue17		OBJECT-TYPE
			SYNTAX	INTEGER
			MAX-ACCESS	read-only
			STATUS	current
			::= { hmWanMbusAF 53 }

hmWanMbusAFVIF18		OBJECT-TYPE
			SYNTAX	INTEGER
			MAX-ACCESS	read-only
			STATUS	current
			::= { hmWanMbusAF 54 }

hmWanMbusAFValue18		OBJECT-TYPE
			SYNTAX	INTEGER
			MAX-ACCESS	read-only
			STATUS	current
			::= { hmWanMbusAF 55 }

hmWanMbusAFVIF19		OBJECT-TYPE
			SYNTAX	INTEGER
			MAX-ACCESS	read-only
			STATUS	current
			::= { hmWanMbusAF 56 }

hmWanMbusAFValue19		OBJECT-TYPE
			SYNTAX	INTEGER
			MAX-ACCESS	read-only
			STATUS	current
			::= { hmWanMbusAF 57 }

hmWanMbusAFVIF1A		OBJECT-TYPE
			SYNTAX	INTEGER
			MAX-ACCESS	read-only
			STATUS	current
			::= { hmWanMbusAF 58 }

hmWanMbusAFValue1A		OBJECT-TYPE
			SYNTAX	INTEGER
			MAX-ACCESS	read-only
			STATUS	current
			::= { hmWanMbusAF 59 }

hmWanMbusAFVIF1B		OBJECT-TYPE
			SYNTAX	INTEGER
			MAX-ACCESS	read-only
			STATUS	current
			::= { hmWanMbusAF 60 }

hmWanMbusAFValue1B		OBJECT-TYPE
			SYNTAX	INTEGER
			MAX-ACCESS	read-only
			STATUS	current
			::= { hmWanMbusAF 61 }

hmWanMbusAFVIF1C		OBJECT-TYPE
			SYNTAX	INTEGER
			MAX-ACCESS	read-only
			STATUS	current
			::= { hmWanMbusAF 62 }

hmWanMbusAFValue1C		OBJECT-TYPE
			SYNTAX	INTEGER
			MAX-ACCESS	read-only
			STATUS	current
			::= { hmWanMbusAF 63 }

hmWanMbusAFVIF1D		OBJECT-TYPE
			SYNTAX	INTEGER
			MAX-ACCESS	read-only
			STATUS	current
			::= { hmWanMbusAF 64 }

hmWanMbusAFValue1D		OBJECT-TYPE
			SYNTAX	INTEGER
			MAX-ACCESS	read-only
			STATUS	current
			::= { hmWanMbusAF 65 }

hmWanMbusAFVIF1E		OBJECT-TYPE
			SYNTAX	INTEGER
			MAX-ACCESS	read-only
			STATUS	current
			::= { hmWanMbusAF 66 }

hmWanMbusAFValue1E		OBJECT-TYPE
			SYNTAX	INTEGER
			MAX-ACCESS	read-only
			STATUS	current
			::= { hmWanMbusAF 67 }

hmWanMbusAFVIF1F		OBJECT-TYPE
			SYNTAX	INTEGER
			MAX-ACCESS	read-only
			STATUS	current
			::= { hmWanMbusAF 68 }

hmWanMbusAFValue1F		OBJECT-TYPE
			SYNTAX	INTEGER
			MAX-ACCESS	read-only
			STATUS	current
			::= { hmWanMbusAF 69 }

hmWanMbusAFVIF20		OBJECT-TYPE
			SYNTAX	INTEGER
			MAX-ACCESS	read-only
			STATUS	current
			::= { hmWanMbusAF 70 }

hmWanMbusAFValue20		OBJECT-TYPE
			SYNTAX	INTEGER
			MAX-ACCESS	read-only
			STATUS	current
			::= { hmWanMbusAF 71 }

hmWanMbusAFVIF21		OBJECT-TYPE
			SYNTAX	INTEGER
			MAX-ACCESS	read-only
			STATUS	current
			::= { hmWanMbusAF 72 }

hmWanMbusAFValue21		OBJECT-TYPE
			SYNTAX	INTEGER
			MAX-ACCESS	read-only
			STATUS	current
			::= { hmWanMbusAF 73 }

hmWanMbusAFVIF22		OBJECT-TYPE
			SYNTAX	INTEGER
			MAX-ACCESS	read-only
			STATUS	current
			::= { hmWanMbusAF 74 }

hmWanMbusAFValue22		OBJECT-TYPE
			SYNTAX	INTEGER
			MAX-ACCESS	read-only
			STATUS	current
			::= { hmWanMbusAF 75 }

hmWanMbusAFVIF23		OBJECT-TYPE
			SYNTAX	INTEGER
			MAX-ACCESS	read-only
			STATUS	current
			::= { hmWanMbusAF 76 }

hmWanMbusAFValue23		OBJECT-TYPE
			SYNTAX	INTEGER
			MAX-ACCESS	read-only
			STATUS	current
			::= { hmWanMbusAF 77 }

hmWanMbusAFVIF24		OBJECT-TYPE
			SYNTAX	INTEGER
			MAX-ACCESS	read-only
			STATUS	current
			::= { hmWanMbusAF 78 }

hmWanMbusAFValue24		OBJECT-TYPE
			SYNTAX	INTEGER
			MAX-ACCESS	read-only
			STATUS	current
			::= { hmWanMbusAF 79 }

hmWanMbusAFVIF25		OBJECT-TYPE
			SYNTAX	INTEGER
			MAX-ACCESS	read-only
			STATUS	current
			::= { hmWanMbusAF 80 }

hmWanMbusAFValue25		OBJECT-TYPE
			SYNTAX	INTEGER
			MAX-ACCESS	read-only
			STATUS	current
			::= { hmWanMbusAF 81 }

hmWanMbusAFVIF26		OBJECT-TYPE
			SYNTAX	INTEGER
			MAX-ACCESS	read-only
			STATUS	current
			::= { hmWanMbusAF 82 }

hmWanMbusAFValue26		OBJECT-TYPE
			SYNTAX	INTEGER
			MAX-ACCESS	read-only
			STATUS	current
			::= { hmWanMbusAF 83 }

hmWanMbusAFVIF27		OBJECT-TYPE
			SYNTAX	INTEGER
			MAX-ACCESS	read-only
			STATUS	current
			::= { hmWanMbusAF 84 }

hmWanMbusAFValue27		OBJECT-TYPE
			SYNTAX	INTEGER
			MAX-ACCESS	read-only
			STATUS	current
			::= { hmWanMbusAF 85 }

hmWanMbusAFVIF28		OBJECT-TYPE
			SYNTAX	INTEGER
			MAX-ACCESS	read-only
			STATUS	current
			::= { hmWanMbusAF 86 }

hmWanMbusAFValue28		OBJECT-TYPE
			SYNTAX	INTEGER
			MAX-ACCESS	read-only
			STATUS	current
			::= { hmWanMbusAF 87 }

hmWanMbusAFVIF29		OBJECT-TYPE
			SYNTAX	INTEGER
			MAX-ACCESS	read-only
			STATUS	current
			::= { hmWanMbusAF 88 }

hmWanMbusAFValue29		OBJECT-TYPE
			SYNTAX	INTEGER
			MAX-ACCESS	read-only
			STATUS	current
			::= { hmWanMbusAF 89 }

hmWanMbusAFVIF2A		OBJECT-TYPE
			SYNTAX	INTEGER
			MAX-ACCESS	read-only
			STATUS	current
			::= { hmWanMbusAF 90 }

hmWanMbusAFValue2A		OBJECT-TYPE
			SYNTAX	INTEGER
			MAX-ACCESS	read-only
			STATUS	current
			::= { hmWanMbusAF 91 }

hmWanMbusAFVIF2B		OBJECT-TYPE
			SYNTAX	INTEGER
			MAX-ACCESS	read-only
			STATUS	current
			::= { hmWanMbusAF 92 }

hmWanMbusAFValue2B		OBJECT-TYPE
			SYNTAX	INTEGER
			MAX-ACCESS	read-only
			STATUS	current
			::= { hmWanMbusAF 93 }

hmWanMbusAFVIF2C		OBJECT-TYPE
			SYNTAX	INTEGER
			MAX-ACCESS	read-only
			STATUS	current
			::= { hmWanMbusAF 94 }

hmWanMbusAFValue2C		OBJECT-TYPE
			SYNTAX	INTEGER
			MAX-ACCESS	read-only
			STATUS	current
			::= { hmWanMbusAF 95 }

hmWanMbusAFVIF2D		OBJECT-TYPE
			SYNTAX	INTEGER
			MAX-ACCESS	read-only
			STATUS	current
			::= { hmWanMbusAF 96 }

hmWanMbusAFValue2D		OBJECT-TYPE
			SYNTAX	INTEGER
			MAX-ACCESS	read-only
			STATUS	current
			::= { hmWanMbusAF 97 }

hmWanMbusAFVIF2E		OBJECT-TYPE
			SYNTAX	INTEGER
			MAX-ACCESS	read-only
			STATUS	current
			::= { hmWanMbusAF 98 }

hmWanMbusAFValue2E		OBJECT-TYPE
			SYNTAX	INTEGER
			MAX-ACCESS	read-only
			STATUS	current
			::= { hmWanMbusAF 99 }

hmWanMbusAFVIF2F		OBJECT-TYPE
			SYNTAX	INTEGER
			MAX-ACCESS	read-only
			STATUS	current
			::= { hmWanMbusAF 100 }

hmWanMbusAFValue2F		OBJECT-TYPE
			SYNTAX	INTEGER
			MAX-ACCESS	read-only
			STATUS	current
			::= { hmWanMbusAF 101 }

hmWanMbusB0			OBJECT IDENTIFIER ::= { hmWanMbus 176 }

hmWanMbusB0IdNumber		OBJECT-TYPE
			SYNTAX	Gauge32
			MAX-ACCESS	read-only
			STATUS	current
			::= { hmWanMbusB0 1 }

hmWanMbusB0Manufacturer	OBJECT-TYPE
			SYNTAX	Gauge32
			MAX-ACCESS	read-only
			STATUS	current
			::= { hmWanMbusB0 2 }

hmWanMbusB0Version		OBJECT-TYPE
			SYNTAX	Gauge32
			MAX-ACCESS	read-only
			STATUS	current
			::= { hmWanMbusB0 3 }

hmWanMbusB0Medium		OBJECT-TYPE
			SYNTAX	Gauge32
			MAX-ACCESS	read-only
			STATUS	current
			::= { hmWanMbusB0 4 }

hmWanMbusB0Status		OBJECT-TYPE
			SYNTAX	Gauge32
			MAX-ACCESS	read-only
			STATUS	current
			::= { hmWanMbusB0 5 }

hmWanMbusB0VIF00		OBJECT-TYPE
			SYNTAX	INTEGER
			MAX-ACCESS	read-only
			STATUS	current
			::= { hmWanMbusB0 6 }

hmWanMbusB0Value00		OBJECT-TYPE
			SYNTAX	INTEGER
			MAX-ACCESS	read-only
			STATUS	current
			::= { hmWanMbusB0 7 }

hmWanMbusB0VIF01		OBJECT-TYPE
			SYNTAX	INTEGER
			MAX-ACCESS	read-only
			STATUS	current
			::= { hmWanMbusB0 8 }

hmWanMbusB0Value01		OBJECT-TYPE
			SYNTAX	INTEGER
			MAX-ACCESS	read-only
			STATUS	current
			::= { hmWanMbusB0 9 }

hmWanMbusB0VIF02		OBJECT-TYPE
			SYNTAX	INTEGER
			MAX-ACCESS	read-only
			STATUS	current
			::= { hmWanMbusB0 10 }

hmWanMbusB0Value02		OBJECT-TYPE
			SYNTAX	INTEGER
			MAX-ACCESS	read-only
			STATUS	current
			::= { hmWanMbusB0 11 }

hmWanMbusB0VIF03		OBJECT-TYPE
			SYNTAX	INTEGER
			MAX-ACCESS	read-only
			STATUS	current
			::= { hmWanMbusB0 12 }

hmWanMbusB0Value03		OBJECT-TYPE
			SYNTAX	INTEGER
			MAX-ACCESS	read-only
			STATUS	current
			::= { hmWanMbusB0 13 }

hmWanMbusB0VIF04		OBJECT-TYPE
			SYNTAX	INTEGER
			MAX-ACCESS	read-only
			STATUS	current
			::= { hmWanMbusB0 14 }

hmWanMbusB0Value04		OBJECT-TYPE
			SYNTAX	INTEGER
			MAX-ACCESS	read-only
			STATUS	current
			::= { hmWanMbusB0 15 }

hmWanMbusB0VIF05		OBJECT-TYPE
			SYNTAX	INTEGER
			MAX-ACCESS	read-only
			STATUS	current
			::= { hmWanMbusB0 16 }

hmWanMbusB0Value05		OBJECT-TYPE
			SYNTAX	INTEGER
			MAX-ACCESS	read-only
			STATUS	current
			::= { hmWanMbusB0 17 }

hmWanMbusB0VIF06		OBJECT-TYPE
			SYNTAX	INTEGER
			MAX-ACCESS	read-only
			STATUS	current
			::= { hmWanMbusB0 18 }

hmWanMbusB0Value06		OBJECT-TYPE
			SYNTAX	INTEGER
			MAX-ACCESS	read-only
			STATUS	current
			::= { hmWanMbusB0 19 }

hmWanMbusB0VIF07		OBJECT-TYPE
			SYNTAX	INTEGER
			MAX-ACCESS	read-only
			STATUS	current
			::= { hmWanMbusB0 20 }

hmWanMbusB0Value07		OBJECT-TYPE
			SYNTAX	INTEGER
			MAX-ACCESS	read-only
			STATUS	current
			::= { hmWanMbusB0 21 }

hmWanMbusB0VIF08		OBJECT-TYPE
			SYNTAX	INTEGER
			MAX-ACCESS	read-only
			STATUS	current
			::= { hmWanMbusB0 22 }

hmWanMbusB0Value08		OBJECT-TYPE
			SYNTAX	INTEGER
			MAX-ACCESS	read-only
			STATUS	current
			::= { hmWanMbusB0 23 }

hmWanMbusB0VIF09		OBJECT-TYPE
			SYNTAX	INTEGER
			MAX-ACCESS	read-only
			STATUS	current
			::= { hmWanMbusB0 24 }

hmWanMbusB0Value09		OBJECT-TYPE
			SYNTAX	INTEGER
			MAX-ACCESS	read-only
			STATUS	current
			::= { hmWanMbusB0 25 }

hmWanMbusB0VIF0A		OBJECT-TYPE
			SYNTAX	INTEGER
			MAX-ACCESS	read-only
			STATUS	current
			::= { hmWanMbusB0 26 }

hmWanMbusB0Value0A		OBJECT-TYPE
			SYNTAX	INTEGER
			MAX-ACCESS	read-only
			STATUS	current
			::= { hmWanMbusB0 27 }

hmWanMbusB0VIF0B		OBJECT-TYPE
			SYNTAX	INTEGER
			MAX-ACCESS	read-only
			STATUS	current
			::= { hmWanMbusB0 28 }

hmWanMbusB0Value0B		OBJECT-TYPE
			SYNTAX	INTEGER
			MAX-ACCESS	read-only
			STATUS	current
			::= { hmWanMbusB0 29 }

hmWanMbusB0VIF0C		OBJECT-TYPE
			SYNTAX	INTEGER
			MAX-ACCESS	read-only
			STATUS	current
			::= { hmWanMbusB0 30 }

hmWanMbusB0Value0C		OBJECT-TYPE
			SYNTAX	INTEGER
			MAX-ACCESS	read-only
			STATUS	current
			::= { hmWanMbusB0 31 }

hmWanMbusB0VIF0D		OBJECT-TYPE
			SYNTAX	INTEGER
			MAX-ACCESS	read-only
			STATUS	current
			::= { hmWanMbusB0 32 }

hmWanMbusB0Value0D		OBJECT-TYPE
			SYNTAX	INTEGER
			MAX-ACCESS	read-only
			STATUS	current
			::= { hmWanMbusB0 33 }

hmWanMbusB0VIF0E		OBJECT-TYPE
			SYNTAX	INTEGER
			MAX-ACCESS	read-only
			STATUS	current
			::= { hmWanMbusB0 34 }

hmWanMbusB0Value0E		OBJECT-TYPE
			SYNTAX	INTEGER
			MAX-ACCESS	read-only
			STATUS	current
			::= { hmWanMbusB0 35 }

hmWanMbusB0VIF0F		OBJECT-TYPE
			SYNTAX	INTEGER
			MAX-ACCESS	read-only
			STATUS	current
			::= { hmWanMbusB0 36 }

hmWanMbusB0Value0F		OBJECT-TYPE
			SYNTAX	INTEGER
			MAX-ACCESS	read-only
			STATUS	current
			::= { hmWanMbusB0 37 }

hmWanMbusB0VIF10		OBJECT-TYPE
			SYNTAX	INTEGER
			MAX-ACCESS	read-only
			STATUS	current
			::= { hmWanMbusB0 38 }

hmWanMbusB0Value10		OBJECT-TYPE
			SYNTAX	INTEGER
			MAX-ACCESS	read-only
			STATUS	current
			::= { hmWanMbusB0 39 }

hmWanMbusB0VIF11		OBJECT-TYPE
			SYNTAX	INTEGER
			MAX-ACCESS	read-only
			STATUS	current
			::= { hmWanMbusB0 40 }

hmWanMbusB0Value11		OBJECT-TYPE
			SYNTAX	INTEGER
			MAX-ACCESS	read-only
			STATUS	current
			::= { hmWanMbusB0 41 }

hmWanMbusB0VIF12		OBJECT-TYPE
			SYNTAX	INTEGER
			MAX-ACCESS	read-only
			STATUS	current
			::= { hmWanMbusB0 42 }

hmWanMbusB0Value12		OBJECT-TYPE
			SYNTAX	INTEGER
			MAX-ACCESS	read-only
			STATUS	current
			::= { hmWanMbusB0 43 }

hmWanMbusB0VIF13		OBJECT-TYPE
			SYNTAX	INTEGER
			MAX-ACCESS	read-only
			STATUS	current
			::= { hmWanMbusB0 44 }

hmWanMbusB0Value13		OBJECT-TYPE
			SYNTAX	INTEGER
			MAX-ACCESS	read-only
			STATUS	current
			::= { hmWanMbusB0 45 }

hmWanMbusB0VIF14		OBJECT-TYPE
			SYNTAX	INTEGER
			MAX-ACCESS	read-only
			STATUS	current
			::= { hmWanMbusB0 46 }

hmWanMbusB0Value14		OBJECT-TYPE
			SYNTAX	INTEGER
			MAX-ACCESS	read-only
			STATUS	current
			::= { hmWanMbusB0 47 }

hmWanMbusB0VIF15		OBJECT-TYPE
			SYNTAX	INTEGER
			MAX-ACCESS	read-only
			STATUS	current
			::= { hmWanMbusB0 48 }

hmWanMbusB0Value15		OBJECT-TYPE
			SYNTAX	INTEGER
			MAX-ACCESS	read-only
			STATUS	current
			::= { hmWanMbusB0 49 }

hmWanMbusB0VIF16		OBJECT-TYPE
			SYNTAX	INTEGER
			MAX-ACCESS	read-only
			STATUS	current
			::= { hmWanMbusB0 50 }

hmWanMbusB0Value16		OBJECT-TYPE
			SYNTAX	INTEGER
			MAX-ACCESS	read-only
			STATUS	current
			::= { hmWanMbusB0 51 }

hmWanMbusB0VIF17		OBJECT-TYPE
			SYNTAX	INTEGER
			MAX-ACCESS	read-only
			STATUS	current
			::= { hmWanMbusB0 52 }

hmWanMbusB0Value17		OBJECT-TYPE
			SYNTAX	INTEGER
			MAX-ACCESS	read-only
			STATUS	current
			::= { hmWanMbusB0 53 }

hmWanMbusB0VIF18		OBJECT-TYPE
			SYNTAX	INTEGER
			MAX-ACCESS	read-only
			STATUS	current
			::= { hmWanMbusB0 54 }

hmWanMbusB0Value18		OBJECT-TYPE
			SYNTAX	INTEGER
			MAX-ACCESS	read-only
			STATUS	current
			::= { hmWanMbusB0 55 }

hmWanMbusB0VIF19		OBJECT-TYPE
			SYNTAX	INTEGER
			MAX-ACCESS	read-only
			STATUS	current
			::= { hmWanMbusB0 56 }

hmWanMbusB0Value19		OBJECT-TYPE
			SYNTAX	INTEGER
			MAX-ACCESS	read-only
			STATUS	current
			::= { hmWanMbusB0 57 }

hmWanMbusB0VIF1A		OBJECT-TYPE
			SYNTAX	INTEGER
			MAX-ACCESS	read-only
			STATUS	current
			::= { hmWanMbusB0 58 }

hmWanMbusB0Value1A		OBJECT-TYPE
			SYNTAX	INTEGER
			MAX-ACCESS	read-only
			STATUS	current
			::= { hmWanMbusB0 59 }

hmWanMbusB0VIF1B		OBJECT-TYPE
			SYNTAX	INTEGER
			MAX-ACCESS	read-only
			STATUS	current
			::= { hmWanMbusB0 60 }

hmWanMbusB0Value1B		OBJECT-TYPE
			SYNTAX	INTEGER
			MAX-ACCESS	read-only
			STATUS	current
			::= { hmWanMbusB0 61 }

hmWanMbusB0VIF1C		OBJECT-TYPE
			SYNTAX	INTEGER
			MAX-ACCESS	read-only
			STATUS	current
			::= { hmWanMbusB0 62 }

hmWanMbusB0Value1C		OBJECT-TYPE
			SYNTAX	INTEGER
			MAX-ACCESS	read-only
			STATUS	current
			::= { hmWanMbusB0 63 }

hmWanMbusB0VIF1D		OBJECT-TYPE
			SYNTAX	INTEGER
			MAX-ACCESS	read-only
			STATUS	current
			::= { hmWanMbusB0 64 }

hmWanMbusB0Value1D		OBJECT-TYPE
			SYNTAX	INTEGER
			MAX-ACCESS	read-only
			STATUS	current
			::= { hmWanMbusB0 65 }

hmWanMbusB0VIF1E		OBJECT-TYPE
			SYNTAX	INTEGER
			MAX-ACCESS	read-only
			STATUS	current
			::= { hmWanMbusB0 66 }

hmWanMbusB0Value1E		OBJECT-TYPE
			SYNTAX	INTEGER
			MAX-ACCESS	read-only
			STATUS	current
			::= { hmWanMbusB0 67 }

hmWanMbusB0VIF1F		OBJECT-TYPE
			SYNTAX	INTEGER
			MAX-ACCESS	read-only
			STATUS	current
			::= { hmWanMbusB0 68 }

hmWanMbusB0Value1F		OBJECT-TYPE
			SYNTAX	INTEGER
			MAX-ACCESS	read-only
			STATUS	current
			::= { hmWanMbusB0 69 }

hmWanMbusB0VIF20		OBJECT-TYPE
			SYNTAX	INTEGER
			MAX-ACCESS	read-only
			STATUS	current
			::= { hmWanMbusB0 70 }

hmWanMbusB0Value20		OBJECT-TYPE
			SYNTAX	INTEGER
			MAX-ACCESS	read-only
			STATUS	current
			::= { hmWanMbusB0 71 }

hmWanMbusB0VIF21		OBJECT-TYPE
			SYNTAX	INTEGER
			MAX-ACCESS	read-only
			STATUS	current
			::= { hmWanMbusB0 72 }

hmWanMbusB0Value21		OBJECT-TYPE
			SYNTAX	INTEGER
			MAX-ACCESS	read-only
			STATUS	current
			::= { hmWanMbusB0 73 }

hmWanMbusB0VIF22		OBJECT-TYPE
			SYNTAX	INTEGER
			MAX-ACCESS	read-only
			STATUS	current
			::= { hmWanMbusB0 74 }

hmWanMbusB0Value22		OBJECT-TYPE
			SYNTAX	INTEGER
			MAX-ACCESS	read-only
			STATUS	current
			::= { hmWanMbusB0 75 }

hmWanMbusB0VIF23		OBJECT-TYPE
			SYNTAX	INTEGER
			MAX-ACCESS	read-only
			STATUS	current
			::= { hmWanMbusB0 76 }

hmWanMbusB0Value23		OBJECT-TYPE
			SYNTAX	INTEGER
			MAX-ACCESS	read-only
			STATUS	current
			::= { hmWanMbusB0 77 }

hmWanMbusB0VIF24		OBJECT-TYPE
			SYNTAX	INTEGER
			MAX-ACCESS	read-only
			STATUS	current
			::= { hmWanMbusB0 78 }

hmWanMbusB0Value24		OBJECT-TYPE
			SYNTAX	INTEGER
			MAX-ACCESS	read-only
			STATUS	current
			::= { hmWanMbusB0 79 }

hmWanMbusB0VIF25		OBJECT-TYPE
			SYNTAX	INTEGER
			MAX-ACCESS	read-only
			STATUS	current
			::= { hmWanMbusB0 80 }

hmWanMbusB0Value25		OBJECT-TYPE
			SYNTAX	INTEGER
			MAX-ACCESS	read-only
			STATUS	current
			::= { hmWanMbusB0 81 }

hmWanMbusB0VIF26		OBJECT-TYPE
			SYNTAX	INTEGER
			MAX-ACCESS	read-only
			STATUS	current
			::= { hmWanMbusB0 82 }

hmWanMbusB0Value26		OBJECT-TYPE
			SYNTAX	INTEGER
			MAX-ACCESS	read-only
			STATUS	current
			::= { hmWanMbusB0 83 }

hmWanMbusB0VIF27		OBJECT-TYPE
			SYNTAX	INTEGER
			MAX-ACCESS	read-only
			STATUS	current
			::= { hmWanMbusB0 84 }

hmWanMbusB0Value27		OBJECT-TYPE
			SYNTAX	INTEGER
			MAX-ACCESS	read-only
			STATUS	current
			::= { hmWanMbusB0 85 }

hmWanMbusB0VIF28		OBJECT-TYPE
			SYNTAX	INTEGER
			MAX-ACCESS	read-only
			STATUS	current
			::= { hmWanMbusB0 86 }

hmWanMbusB0Value28		OBJECT-TYPE
			SYNTAX	INTEGER
			MAX-ACCESS	read-only
			STATUS	current
			::= { hmWanMbusB0 87 }

hmWanMbusB0VIF29		OBJECT-TYPE
			SYNTAX	INTEGER
			MAX-ACCESS	read-only
			STATUS	current
			::= { hmWanMbusB0 88 }

hmWanMbusB0Value29		OBJECT-TYPE
			SYNTAX	INTEGER
			MAX-ACCESS	read-only
			STATUS	current
			::= { hmWanMbusB0 89 }

hmWanMbusB0VIF2A		OBJECT-TYPE
			SYNTAX	INTEGER
			MAX-ACCESS	read-only
			STATUS	current
			::= { hmWanMbusB0 90 }

hmWanMbusB0Value2A		OBJECT-TYPE
			SYNTAX	INTEGER
			MAX-ACCESS	read-only
			STATUS	current
			::= { hmWanMbusB0 91 }

hmWanMbusB0VIF2B		OBJECT-TYPE
			SYNTAX	INTEGER
			MAX-ACCESS	read-only
			STATUS	current
			::= { hmWanMbusB0 92 }

hmWanMbusB0Value2B		OBJECT-TYPE
			SYNTAX	INTEGER
			MAX-ACCESS	read-only
			STATUS	current
			::= { hmWanMbusB0 93 }

hmWanMbusB0VIF2C		OBJECT-TYPE
			SYNTAX	INTEGER
			MAX-ACCESS	read-only
			STATUS	current
			::= { hmWanMbusB0 94 }

hmWanMbusB0Value2C		OBJECT-TYPE
			SYNTAX	INTEGER
			MAX-ACCESS	read-only
			STATUS	current
			::= { hmWanMbusB0 95 }

hmWanMbusB0VIF2D		OBJECT-TYPE
			SYNTAX	INTEGER
			MAX-ACCESS	read-only
			STATUS	current
			::= { hmWanMbusB0 96 }

hmWanMbusB0Value2D		OBJECT-TYPE
			SYNTAX	INTEGER
			MAX-ACCESS	read-only
			STATUS	current
			::= { hmWanMbusB0 97 }

hmWanMbusB0VIF2E		OBJECT-TYPE
			SYNTAX	INTEGER
			MAX-ACCESS	read-only
			STATUS	current
			::= { hmWanMbusB0 98 }

hmWanMbusB0Value2E		OBJECT-TYPE
			SYNTAX	INTEGER
			MAX-ACCESS	read-only
			STATUS	current
			::= { hmWanMbusB0 99 }

hmWanMbusB0VIF2F		OBJECT-TYPE
			SYNTAX	INTEGER
			MAX-ACCESS	read-only
			STATUS	current
			::= { hmWanMbusB0 100 }

hmWanMbusB0Value2F		OBJECT-TYPE
			SYNTAX	INTEGER
			MAX-ACCESS	read-only
			STATUS	current
			::= { hmWanMbusB0 101 }

hmWanMbusB1			OBJECT IDENTIFIER ::= { hmWanMbus 177 }

hmWanMbusB1IdNumber		OBJECT-TYPE
			SYNTAX	Gauge32
			MAX-ACCESS	read-only
			STATUS	current
			::= { hmWanMbusB1 1 }

hmWanMbusB1Manufacturer	OBJECT-TYPE
			SYNTAX	Gauge32
			MAX-ACCESS	read-only
			STATUS	current
			::= { hmWanMbusB1 2 }

hmWanMbusB1Version		OBJECT-TYPE
			SYNTAX	Gauge32
			MAX-ACCESS	read-only
			STATUS	current
			::= { hmWanMbusB1 3 }

hmWanMbusB1Medium		OBJECT-TYPE
			SYNTAX	Gauge32
			MAX-ACCESS	read-only
			STATUS	current
			::= { hmWanMbusB1 4 }

hmWanMbusB1Status		OBJECT-TYPE
			SYNTAX	Gauge32
			MAX-ACCESS	read-only
			STATUS	current
			::= { hmWanMbusB1 5 }

hmWanMbusB1VIF00		OBJECT-TYPE
			SYNTAX	INTEGER
			MAX-ACCESS	read-only
			STATUS	current
			::= { hmWanMbusB1 6 }

hmWanMbusB1Value00		OBJECT-TYPE
			SYNTAX	INTEGER
			MAX-ACCESS	read-only
			STATUS	current
			::= { hmWanMbusB1 7 }

hmWanMbusB1VIF01		OBJECT-TYPE
			SYNTAX	INTEGER
			MAX-ACCESS	read-only
			STATUS	current
			::= { hmWanMbusB1 8 }

hmWanMbusB1Value01		OBJECT-TYPE
			SYNTAX	INTEGER
			MAX-ACCESS	read-only
			STATUS	current
			::= { hmWanMbusB1 9 }

hmWanMbusB1VIF02		OBJECT-TYPE
			SYNTAX	INTEGER
			MAX-ACCESS	read-only
			STATUS	current
			::= { hmWanMbusB1 10 }

hmWanMbusB1Value02		OBJECT-TYPE
			SYNTAX	INTEGER
			MAX-ACCESS	read-only
			STATUS	current
			::= { hmWanMbusB1 11 }

hmWanMbusB1VIF03		OBJECT-TYPE
			SYNTAX	INTEGER
			MAX-ACCESS	read-only
			STATUS	current
			::= { hmWanMbusB1 12 }

hmWanMbusB1Value03		OBJECT-TYPE
			SYNTAX	INTEGER
			MAX-ACCESS	read-only
			STATUS	current
			::= { hmWanMbusB1 13 }

hmWanMbusB1VIF04		OBJECT-TYPE
			SYNTAX	INTEGER
			MAX-ACCESS	read-only
			STATUS	current
			::= { hmWanMbusB1 14 }

hmWanMbusB1Value04		OBJECT-TYPE
			SYNTAX	INTEGER
			MAX-ACCESS	read-only
			STATUS	current
			::= { hmWanMbusB1 15 }

hmWanMbusB1VIF05		OBJECT-TYPE
			SYNTAX	INTEGER
			MAX-ACCESS	read-only
			STATUS	current
			::= { hmWanMbusB1 16 }

hmWanMbusB1Value05		OBJECT-TYPE
			SYNTAX	INTEGER
			MAX-ACCESS	read-only
			STATUS	current
			::= { hmWanMbusB1 17 }

hmWanMbusB1VIF06		OBJECT-TYPE
			SYNTAX	INTEGER
			MAX-ACCESS	read-only
			STATUS	current
			::= { hmWanMbusB1 18 }

hmWanMbusB1Value06		OBJECT-TYPE
			SYNTAX	INTEGER
			MAX-ACCESS	read-only
			STATUS	current
			::= { hmWanMbusB1 19 }

hmWanMbusB1VIF07		OBJECT-TYPE
			SYNTAX	INTEGER
			MAX-ACCESS	read-only
			STATUS	current
			::= { hmWanMbusB1 20 }

hmWanMbusB1Value07		OBJECT-TYPE
			SYNTAX	INTEGER
			MAX-ACCESS	read-only
			STATUS	current
			::= { hmWanMbusB1 21 }

hmWanMbusB1VIF08		OBJECT-TYPE
			SYNTAX	INTEGER
			MAX-ACCESS	read-only
			STATUS	current
			::= { hmWanMbusB1 22 }

hmWanMbusB1Value08		OBJECT-TYPE
			SYNTAX	INTEGER
			MAX-ACCESS	read-only
			STATUS	current
			::= { hmWanMbusB1 23 }

hmWanMbusB1VIF09		OBJECT-TYPE
			SYNTAX	INTEGER
			MAX-ACCESS	read-only
			STATUS	current
			::= { hmWanMbusB1 24 }

hmWanMbusB1Value09		OBJECT-TYPE
			SYNTAX	INTEGER
			MAX-ACCESS	read-only
			STATUS	current
			::= { hmWanMbusB1 25 }

hmWanMbusB1VIF0A		OBJECT-TYPE
			SYNTAX	INTEGER
			MAX-ACCESS	read-only
			STATUS	current
			::= { hmWanMbusB1 26 }

hmWanMbusB1Value0A		OBJECT-TYPE
			SYNTAX	INTEGER
			MAX-ACCESS	read-only
			STATUS	current
			::= { hmWanMbusB1 27 }

hmWanMbusB1VIF0B		OBJECT-TYPE
			SYNTAX	INTEGER
			MAX-ACCESS	read-only
			STATUS	current
			::= { hmWanMbusB1 28 }

hmWanMbusB1Value0B		OBJECT-TYPE
			SYNTAX	INTEGER
			MAX-ACCESS	read-only
			STATUS	current
			::= { hmWanMbusB1 29 }

hmWanMbusB1VIF0C		OBJECT-TYPE
			SYNTAX	INTEGER
			MAX-ACCESS	read-only
			STATUS	current
			::= { hmWanMbusB1 30 }

hmWanMbusB1Value0C		OBJECT-TYPE
			SYNTAX	INTEGER
			MAX-ACCESS	read-only
			STATUS	current
			::= { hmWanMbusB1 31 }

hmWanMbusB1VIF0D		OBJECT-TYPE
			SYNTAX	INTEGER
			MAX-ACCESS	read-only
			STATUS	current
			::= { hmWanMbusB1 32 }

hmWanMbusB1Value0D		OBJECT-TYPE
			SYNTAX	INTEGER
			MAX-ACCESS	read-only
			STATUS	current
			::= { hmWanMbusB1 33 }

hmWanMbusB1VIF0E		OBJECT-TYPE
			SYNTAX	INTEGER
			MAX-ACCESS	read-only
			STATUS	current
			::= { hmWanMbusB1 34 }

hmWanMbusB1Value0E		OBJECT-TYPE
			SYNTAX	INTEGER
			MAX-ACCESS	read-only
			STATUS	current
			::= { hmWanMbusB1 35 }

hmWanMbusB1VIF0F		OBJECT-TYPE
			SYNTAX	INTEGER
			MAX-ACCESS	read-only
			STATUS	current
			::= { hmWanMbusB1 36 }

hmWanMbusB1Value0F		OBJECT-TYPE
			SYNTAX	INTEGER
			MAX-ACCESS	read-only
			STATUS	current
			::= { hmWanMbusB1 37 }

hmWanMbusB1VIF10		OBJECT-TYPE
			SYNTAX	INTEGER
			MAX-ACCESS	read-only
			STATUS	current
			::= { hmWanMbusB1 38 }

hmWanMbusB1Value10		OBJECT-TYPE
			SYNTAX	INTEGER
			MAX-ACCESS	read-only
			STATUS	current
			::= { hmWanMbusB1 39 }

hmWanMbusB1VIF11		OBJECT-TYPE
			SYNTAX	INTEGER
			MAX-ACCESS	read-only
			STATUS	current
			::= { hmWanMbusB1 40 }

hmWanMbusB1Value11		OBJECT-TYPE
			SYNTAX	INTEGER
			MAX-ACCESS	read-only
			STATUS	current
			::= { hmWanMbusB1 41 }

hmWanMbusB1VIF12		OBJECT-TYPE
			SYNTAX	INTEGER
			MAX-ACCESS	read-only
			STATUS	current
			::= { hmWanMbusB1 42 }

hmWanMbusB1Value12		OBJECT-TYPE
			SYNTAX	INTEGER
			MAX-ACCESS	read-only
			STATUS	current
			::= { hmWanMbusB1 43 }

hmWanMbusB1VIF13		OBJECT-TYPE
			SYNTAX	INTEGER
			MAX-ACCESS	read-only
			STATUS	current
			::= { hmWanMbusB1 44 }

hmWanMbusB1Value13		OBJECT-TYPE
			SYNTAX	INTEGER
			MAX-ACCESS	read-only
			STATUS	current
			::= { hmWanMbusB1 45 }

hmWanMbusB1VIF14		OBJECT-TYPE
			SYNTAX	INTEGER
			MAX-ACCESS	read-only
			STATUS	current
			::= { hmWanMbusB1 46 }

hmWanMbusB1Value14		OBJECT-TYPE
			SYNTAX	INTEGER
			MAX-ACCESS	read-only
			STATUS	current
			::= { hmWanMbusB1 47 }

hmWanMbusB1VIF15		OBJECT-TYPE
			SYNTAX	INTEGER
			MAX-ACCESS	read-only
			STATUS	current
			::= { hmWanMbusB1 48 }

hmWanMbusB1Value15		OBJECT-TYPE
			SYNTAX	INTEGER
			MAX-ACCESS	read-only
			STATUS	current
			::= { hmWanMbusB1 49 }

hmWanMbusB1VIF16		OBJECT-TYPE
			SYNTAX	INTEGER
			MAX-ACCESS	read-only
			STATUS	current
			::= { hmWanMbusB1 50 }

hmWanMbusB1Value16		OBJECT-TYPE
			SYNTAX	INTEGER
			MAX-ACCESS	read-only
			STATUS	current
			::= { hmWanMbusB1 51 }

hmWanMbusB1VIF17		OBJECT-TYPE
			SYNTAX	INTEGER
			MAX-ACCESS	read-only
			STATUS	current
			::= { hmWanMbusB1 52 }

hmWanMbusB1Value17		OBJECT-TYPE
			SYNTAX	INTEGER
			MAX-ACCESS	read-only
			STATUS	current
			::= { hmWanMbusB1 53 }

hmWanMbusB1VIF18		OBJECT-TYPE
			SYNTAX	INTEGER
			MAX-ACCESS	read-only
			STATUS	current
			::= { hmWanMbusB1 54 }

hmWanMbusB1Value18		OBJECT-TYPE
			SYNTAX	INTEGER
			MAX-ACCESS	read-only
			STATUS	current
			::= { hmWanMbusB1 55 }

hmWanMbusB1VIF19		OBJECT-TYPE
			SYNTAX	INTEGER
			MAX-ACCESS	read-only
			STATUS	current
			::= { hmWanMbusB1 56 }

hmWanMbusB1Value19		OBJECT-TYPE
			SYNTAX	INTEGER
			MAX-ACCESS	read-only
			STATUS	current
			::= { hmWanMbusB1 57 }

hmWanMbusB1VIF1A		OBJECT-TYPE
			SYNTAX	INTEGER
			MAX-ACCESS	read-only
			STATUS	current
			::= { hmWanMbusB1 58 }

hmWanMbusB1Value1A		OBJECT-TYPE
			SYNTAX	INTEGER
			MAX-ACCESS	read-only
			STATUS	current
			::= { hmWanMbusB1 59 }

hmWanMbusB1VIF1B		OBJECT-TYPE
			SYNTAX	INTEGER
			MAX-ACCESS	read-only
			STATUS	current
			::= { hmWanMbusB1 60 }

hmWanMbusB1Value1B		OBJECT-TYPE
			SYNTAX	INTEGER
			MAX-ACCESS	read-only
			STATUS	current
			::= { hmWanMbusB1 61 }

hmWanMbusB1VIF1C		OBJECT-TYPE
			SYNTAX	INTEGER
			MAX-ACCESS	read-only
			STATUS	current
			::= { hmWanMbusB1 62 }

hmWanMbusB1Value1C		OBJECT-TYPE
			SYNTAX	INTEGER
			MAX-ACCESS	read-only
			STATUS	current
			::= { hmWanMbusB1 63 }

hmWanMbusB1VIF1D		OBJECT-TYPE
			SYNTAX	INTEGER
			MAX-ACCESS	read-only
			STATUS	current
			::= { hmWanMbusB1 64 }

hmWanMbusB1Value1D		OBJECT-TYPE
			SYNTAX	INTEGER
			MAX-ACCESS	read-only
			STATUS	current
			::= { hmWanMbusB1 65 }

hmWanMbusB1VIF1E		OBJECT-TYPE
			SYNTAX	INTEGER
			MAX-ACCESS	read-only
			STATUS	current
			::= { hmWanMbusB1 66 }

hmWanMbusB1Value1E		OBJECT-TYPE
			SYNTAX	INTEGER
			MAX-ACCESS	read-only
			STATUS	current
			::= { hmWanMbusB1 67 }

hmWanMbusB1VIF1F		OBJECT-TYPE
			SYNTAX	INTEGER
			MAX-ACCESS	read-only
			STATUS	current
			::= { hmWanMbusB1 68 }

hmWanMbusB1Value1F		OBJECT-TYPE
			SYNTAX	INTEGER
			MAX-ACCESS	read-only
			STATUS	current
			::= { hmWanMbusB1 69 }

hmWanMbusB1VIF20		OBJECT-TYPE
			SYNTAX	INTEGER
			MAX-ACCESS	read-only
			STATUS	current
			::= { hmWanMbusB1 70 }

hmWanMbusB1Value20		OBJECT-TYPE
			SYNTAX	INTEGER
			MAX-ACCESS	read-only
			STATUS	current
			::= { hmWanMbusB1 71 }

hmWanMbusB1VIF21		OBJECT-TYPE
			SYNTAX	INTEGER
			MAX-ACCESS	read-only
			STATUS	current
			::= { hmWanMbusB1 72 }

hmWanMbusB1Value21		OBJECT-TYPE
			SYNTAX	INTEGER
			MAX-ACCESS	read-only
			STATUS	current
			::= { hmWanMbusB1 73 }

hmWanMbusB1VIF22		OBJECT-TYPE
			SYNTAX	INTEGER
			MAX-ACCESS	read-only
			STATUS	current
			::= { hmWanMbusB1 74 }

hmWanMbusB1Value22		OBJECT-TYPE
			SYNTAX	INTEGER
			MAX-ACCESS	read-only
			STATUS	current
			::= { hmWanMbusB1 75 }

hmWanMbusB1VIF23		OBJECT-TYPE
			SYNTAX	INTEGER
			MAX-ACCESS	read-only
			STATUS	current
			::= { hmWanMbusB1 76 }

hmWanMbusB1Value23		OBJECT-TYPE
			SYNTAX	INTEGER
			MAX-ACCESS	read-only
			STATUS	current
			::= { hmWanMbusB1 77 }

hmWanMbusB1VIF24		OBJECT-TYPE
			SYNTAX	INTEGER
			MAX-ACCESS	read-only
			STATUS	current
			::= { hmWanMbusB1 78 }

hmWanMbusB1Value24		OBJECT-TYPE
			SYNTAX	INTEGER
			MAX-ACCESS	read-only
			STATUS	current
			::= { hmWanMbusB1 79 }

hmWanMbusB1VIF25		OBJECT-TYPE
			SYNTAX	INTEGER
			MAX-ACCESS	read-only
			STATUS	current
			::= { hmWanMbusB1 80 }

hmWanMbusB1Value25		OBJECT-TYPE
			SYNTAX	INTEGER
			MAX-ACCESS	read-only
			STATUS	current
			::= { hmWanMbusB1 81 }

hmWanMbusB1VIF26		OBJECT-TYPE
			SYNTAX	INTEGER
			MAX-ACCESS	read-only
			STATUS	current
			::= { hmWanMbusB1 82 }

hmWanMbusB1Value26		OBJECT-TYPE
			SYNTAX	INTEGER
			MAX-ACCESS	read-only
			STATUS	current
			::= { hmWanMbusB1 83 }

hmWanMbusB1VIF27		OBJECT-TYPE
			SYNTAX	INTEGER
			MAX-ACCESS	read-only
			STATUS	current
			::= { hmWanMbusB1 84 }

hmWanMbusB1Value27		OBJECT-TYPE
			SYNTAX	INTEGER
			MAX-ACCESS	read-only
			STATUS	current
			::= { hmWanMbusB1 85 }

hmWanMbusB1VIF28		OBJECT-TYPE
			SYNTAX	INTEGER
			MAX-ACCESS	read-only
			STATUS	current
			::= { hmWanMbusB1 86 }

hmWanMbusB1Value28		OBJECT-TYPE
			SYNTAX	INTEGER
			MAX-ACCESS	read-only
			STATUS	current
			::= { hmWanMbusB1 87 }

hmWanMbusB1VIF29		OBJECT-TYPE
			SYNTAX	INTEGER
			MAX-ACCESS	read-only
			STATUS	current
			::= { hmWanMbusB1 88 }

hmWanMbusB1Value29		OBJECT-TYPE
			SYNTAX	INTEGER
			MAX-ACCESS	read-only
			STATUS	current
			::= { hmWanMbusB1 89 }

hmWanMbusB1VIF2A		OBJECT-TYPE
			SYNTAX	INTEGER
			MAX-ACCESS	read-only
			STATUS	current
			::= { hmWanMbusB1 90 }

hmWanMbusB1Value2A		OBJECT-TYPE
			SYNTAX	INTEGER
			MAX-ACCESS	read-only
			STATUS	current
			::= { hmWanMbusB1 91 }

hmWanMbusB1VIF2B		OBJECT-TYPE
			SYNTAX	INTEGER
			MAX-ACCESS	read-only
			STATUS	current
			::= { hmWanMbusB1 92 }

hmWanMbusB1Value2B		OBJECT-TYPE
			SYNTAX	INTEGER
			MAX-ACCESS	read-only
			STATUS	current
			::= { hmWanMbusB1 93 }

hmWanMbusB1VIF2C		OBJECT-TYPE
			SYNTAX	INTEGER
			MAX-ACCESS	read-only
			STATUS	current
			::= { hmWanMbusB1 94 }

hmWanMbusB1Value2C		OBJECT-TYPE
			SYNTAX	INTEGER
			MAX-ACCESS	read-only
			STATUS	current
			::= { hmWanMbusB1 95 }

hmWanMbusB1VIF2D		OBJECT-TYPE
			SYNTAX	INTEGER
			MAX-ACCESS	read-only
			STATUS	current
			::= { hmWanMbusB1 96 }

hmWanMbusB1Value2D		OBJECT-TYPE
			SYNTAX	INTEGER
			MAX-ACCESS	read-only
			STATUS	current
			::= { hmWanMbusB1 97 }

hmWanMbusB1VIF2E		OBJECT-TYPE
			SYNTAX	INTEGER
			MAX-ACCESS	read-only
			STATUS	current
			::= { hmWanMbusB1 98 }

hmWanMbusB1Value2E		OBJECT-TYPE
			SYNTAX	INTEGER
			MAX-ACCESS	read-only
			STATUS	current
			::= { hmWanMbusB1 99 }

hmWanMbusB1VIF2F		OBJECT-TYPE
			SYNTAX	INTEGER
			MAX-ACCESS	read-only
			STATUS	current
			::= { hmWanMbusB1 100 }

hmWanMbusB1Value2F		OBJECT-TYPE
			SYNTAX	INTEGER
			MAX-ACCESS	read-only
			STATUS	current
			::= { hmWanMbusB1 101 }

hmWanMbusB2			OBJECT IDENTIFIER ::= { hmWanMbus 178 }

hmWanMbusB2IdNumber		OBJECT-TYPE
			SYNTAX	Gauge32
			MAX-ACCESS	read-only
			STATUS	current
			::= { hmWanMbusB2 1 }

hmWanMbusB2Manufacturer	OBJECT-TYPE
			SYNTAX	Gauge32
			MAX-ACCESS	read-only
			STATUS	current
			::= { hmWanMbusB2 2 }

hmWanMbusB2Version		OBJECT-TYPE
			SYNTAX	Gauge32
			MAX-ACCESS	read-only
			STATUS	current
			::= { hmWanMbusB2 3 }

hmWanMbusB2Medium		OBJECT-TYPE
			SYNTAX	Gauge32
			MAX-ACCESS	read-only
			STATUS	current
			::= { hmWanMbusB2 4 }

hmWanMbusB2Status		OBJECT-TYPE
			SYNTAX	Gauge32
			MAX-ACCESS	read-only
			STATUS	current
			::= { hmWanMbusB2 5 }

hmWanMbusB2VIF00		OBJECT-TYPE
			SYNTAX	INTEGER
			MAX-ACCESS	read-only
			STATUS	current
			::= { hmWanMbusB2 6 }

hmWanMbusB2Value00		OBJECT-TYPE
			SYNTAX	INTEGER
			MAX-ACCESS	read-only
			STATUS	current
			::= { hmWanMbusB2 7 }

hmWanMbusB2VIF01		OBJECT-TYPE
			SYNTAX	INTEGER
			MAX-ACCESS	read-only
			STATUS	current
			::= { hmWanMbusB2 8 }

hmWanMbusB2Value01		OBJECT-TYPE
			SYNTAX	INTEGER
			MAX-ACCESS	read-only
			STATUS	current
			::= { hmWanMbusB2 9 }

hmWanMbusB2VIF02		OBJECT-TYPE
			SYNTAX	INTEGER
			MAX-ACCESS	read-only
			STATUS	current
			::= { hmWanMbusB2 10 }

hmWanMbusB2Value02		OBJECT-TYPE
			SYNTAX	INTEGER
			MAX-ACCESS	read-only
			STATUS	current
			::= { hmWanMbusB2 11 }

hmWanMbusB2VIF03		OBJECT-TYPE
			SYNTAX	INTEGER
			MAX-ACCESS	read-only
			STATUS	current
			::= { hmWanMbusB2 12 }

hmWanMbusB2Value03		OBJECT-TYPE
			SYNTAX	INTEGER
			MAX-ACCESS	read-only
			STATUS	current
			::= { hmWanMbusB2 13 }

hmWanMbusB2VIF04		OBJECT-TYPE
			SYNTAX	INTEGER
			MAX-ACCESS	read-only
			STATUS	current
			::= { hmWanMbusB2 14 }

hmWanMbusB2Value04		OBJECT-TYPE
			SYNTAX	INTEGER
			MAX-ACCESS	read-only
			STATUS	current
			::= { hmWanMbusB2 15 }

hmWanMbusB2VIF05		OBJECT-TYPE
			SYNTAX	INTEGER
			MAX-ACCESS	read-only
			STATUS	current
			::= { hmWanMbusB2 16 }

hmWanMbusB2Value05		OBJECT-TYPE
			SYNTAX	INTEGER
			MAX-ACCESS	read-only
			STATUS	current
			::= { hmWanMbusB2 17 }

hmWanMbusB2VIF06		OBJECT-TYPE
			SYNTAX	INTEGER
			MAX-ACCESS	read-only
			STATUS	current
			::= { hmWanMbusB2 18 }

hmWanMbusB2Value06		OBJECT-TYPE
			SYNTAX	INTEGER
			MAX-ACCESS	read-only
			STATUS	current
			::= { hmWanMbusB2 19 }

hmWanMbusB2VIF07		OBJECT-TYPE
			SYNTAX	INTEGER
			MAX-ACCESS	read-only
			STATUS	current
			::= { hmWanMbusB2 20 }

hmWanMbusB2Value07		OBJECT-TYPE
			SYNTAX	INTEGER
			MAX-ACCESS	read-only
			STATUS	current
			::= { hmWanMbusB2 21 }

hmWanMbusB2VIF08		OBJECT-TYPE
			SYNTAX	INTEGER
			MAX-ACCESS	read-only
			STATUS	current
			::= { hmWanMbusB2 22 }

hmWanMbusB2Value08		OBJECT-TYPE
			SYNTAX	INTEGER
			MAX-ACCESS	read-only
			STATUS	current
			::= { hmWanMbusB2 23 }

hmWanMbusB2VIF09		OBJECT-TYPE
			SYNTAX	INTEGER
			MAX-ACCESS	read-only
			STATUS	current
			::= { hmWanMbusB2 24 }

hmWanMbusB2Value09		OBJECT-TYPE
			SYNTAX	INTEGER
			MAX-ACCESS	read-only
			STATUS	current
			::= { hmWanMbusB2 25 }

hmWanMbusB2VIF0A		OBJECT-TYPE
			SYNTAX	INTEGER
			MAX-ACCESS	read-only
			STATUS	current
			::= { hmWanMbusB2 26 }

hmWanMbusB2Value0A		OBJECT-TYPE
			SYNTAX	INTEGER
			MAX-ACCESS	read-only
			STATUS	current
			::= { hmWanMbusB2 27 }

hmWanMbusB2VIF0B		OBJECT-TYPE
			SYNTAX	INTEGER
			MAX-ACCESS	read-only
			STATUS	current
			::= { hmWanMbusB2 28 }

hmWanMbusB2Value0B		OBJECT-TYPE
			SYNTAX	INTEGER
			MAX-ACCESS	read-only
			STATUS	current
			::= { hmWanMbusB2 29 }

hmWanMbusB2VIF0C		OBJECT-TYPE
			SYNTAX	INTEGER
			MAX-ACCESS	read-only
			STATUS	current
			::= { hmWanMbusB2 30 }

hmWanMbusB2Value0C		OBJECT-TYPE
			SYNTAX	INTEGER
			MAX-ACCESS	read-only
			STATUS	current
			::= { hmWanMbusB2 31 }

hmWanMbusB2VIF0D		OBJECT-TYPE
			SYNTAX	INTEGER
			MAX-ACCESS	read-only
			STATUS	current
			::= { hmWanMbusB2 32 }

hmWanMbusB2Value0D		OBJECT-TYPE
			SYNTAX	INTEGER
			MAX-ACCESS	read-only
			STATUS	current
			::= { hmWanMbusB2 33 }

hmWanMbusB2VIF0E		OBJECT-TYPE
			SYNTAX	INTEGER
			MAX-ACCESS	read-only
			STATUS	current
			::= { hmWanMbusB2 34 }

hmWanMbusB2Value0E		OBJECT-TYPE
			SYNTAX	INTEGER
			MAX-ACCESS	read-only
			STATUS	current
			::= { hmWanMbusB2 35 }

hmWanMbusB2VIF0F		OBJECT-TYPE
			SYNTAX	INTEGER
			MAX-ACCESS	read-only
			STATUS	current
			::= { hmWanMbusB2 36 }

hmWanMbusB2Value0F		OBJECT-TYPE
			SYNTAX	INTEGER
			MAX-ACCESS	read-only
			STATUS	current
			::= { hmWanMbusB2 37 }

hmWanMbusB2VIF10		OBJECT-TYPE
			SYNTAX	INTEGER
			MAX-ACCESS	read-only
			STATUS	current
			::= { hmWanMbusB2 38 }

hmWanMbusB2Value10		OBJECT-TYPE
			SYNTAX	INTEGER
			MAX-ACCESS	read-only
			STATUS	current
			::= { hmWanMbusB2 39 }

hmWanMbusB2VIF11		OBJECT-TYPE
			SYNTAX	INTEGER
			MAX-ACCESS	read-only
			STATUS	current
			::= { hmWanMbusB2 40 }

hmWanMbusB2Value11		OBJECT-TYPE
			SYNTAX	INTEGER
			MAX-ACCESS	read-only
			STATUS	current
			::= { hmWanMbusB2 41 }

hmWanMbusB2VIF12		OBJECT-TYPE
			SYNTAX	INTEGER
			MAX-ACCESS	read-only
			STATUS	current
			::= { hmWanMbusB2 42 }

hmWanMbusB2Value12		OBJECT-TYPE
			SYNTAX	INTEGER
			MAX-ACCESS	read-only
			STATUS	current
			::= { hmWanMbusB2 43 }

hmWanMbusB2VIF13		OBJECT-TYPE
			SYNTAX	INTEGER
			MAX-ACCESS	read-only
			STATUS	current
			::= { hmWanMbusB2 44 }

hmWanMbusB2Value13		OBJECT-TYPE
			SYNTAX	INTEGER
			MAX-ACCESS	read-only
			STATUS	current
			::= { hmWanMbusB2 45 }

hmWanMbusB2VIF14		OBJECT-TYPE
			SYNTAX	INTEGER
			MAX-ACCESS	read-only
			STATUS	current
			::= { hmWanMbusB2 46 }

hmWanMbusB2Value14		OBJECT-TYPE
			SYNTAX	INTEGER
			MAX-ACCESS	read-only
			STATUS	current
			::= { hmWanMbusB2 47 }

hmWanMbusB2VIF15		OBJECT-TYPE
			SYNTAX	INTEGER
			MAX-ACCESS	read-only
			STATUS	current
			::= { hmWanMbusB2 48 }

hmWanMbusB2Value15		OBJECT-TYPE
			SYNTAX	INTEGER
			MAX-ACCESS	read-only
			STATUS	current
			::= { hmWanMbusB2 49 }

hmWanMbusB2VIF16		OBJECT-TYPE
			SYNTAX	INTEGER
			MAX-ACCESS	read-only
			STATUS	current
			::= { hmWanMbusB2 50 }

hmWanMbusB2Value16		OBJECT-TYPE
			SYNTAX	INTEGER
			MAX-ACCESS	read-only
			STATUS	current
			::= { hmWanMbusB2 51 }

hmWanMbusB2VIF17		OBJECT-TYPE
			SYNTAX	INTEGER
			MAX-ACCESS	read-only
			STATUS	current
			::= { hmWanMbusB2 52 }

hmWanMbusB2Value17		OBJECT-TYPE
			SYNTAX	INTEGER
			MAX-ACCESS	read-only
			STATUS	current
			::= { hmWanMbusB2 53 }

hmWanMbusB2VIF18		OBJECT-TYPE
			SYNTAX	INTEGER
			MAX-ACCESS	read-only
			STATUS	current
			::= { hmWanMbusB2 54 }

hmWanMbusB2Value18		OBJECT-TYPE
			SYNTAX	INTEGER
			MAX-ACCESS	read-only
			STATUS	current
			::= { hmWanMbusB2 55 }

hmWanMbusB2VIF19		OBJECT-TYPE
			SYNTAX	INTEGER
			MAX-ACCESS	read-only
			STATUS	current
			::= { hmWanMbusB2 56 }

hmWanMbusB2Value19		OBJECT-TYPE
			SYNTAX	INTEGER
			MAX-ACCESS	read-only
			STATUS	current
			::= { hmWanMbusB2 57 }

hmWanMbusB2VIF1A		OBJECT-TYPE
			SYNTAX	INTEGER
			MAX-ACCESS	read-only
			STATUS	current
			::= { hmWanMbusB2 58 }

hmWanMbusB2Value1A		OBJECT-TYPE
			SYNTAX	INTEGER
			MAX-ACCESS	read-only
			STATUS	current
			::= { hmWanMbusB2 59 }

hmWanMbusB2VIF1B		OBJECT-TYPE
			SYNTAX	INTEGER
			MAX-ACCESS	read-only
			STATUS	current
			::= { hmWanMbusB2 60 }

hmWanMbusB2Value1B		OBJECT-TYPE
			SYNTAX	INTEGER
			MAX-ACCESS	read-only
			STATUS	current
			::= { hmWanMbusB2 61 }

hmWanMbusB2VIF1C		OBJECT-TYPE
			SYNTAX	INTEGER
			MAX-ACCESS	read-only
			STATUS	current
			::= { hmWanMbusB2 62 }

hmWanMbusB2Value1C		OBJECT-TYPE
			SYNTAX	INTEGER
			MAX-ACCESS	read-only
			STATUS	current
			::= { hmWanMbusB2 63 }

hmWanMbusB2VIF1D		OBJECT-TYPE
			SYNTAX	INTEGER
			MAX-ACCESS	read-only
			STATUS	current
			::= { hmWanMbusB2 64 }

hmWanMbusB2Value1D		OBJECT-TYPE
			SYNTAX	INTEGER
			MAX-ACCESS	read-only
			STATUS	current
			::= { hmWanMbusB2 65 }

hmWanMbusB2VIF1E		OBJECT-TYPE
			SYNTAX	INTEGER
			MAX-ACCESS	read-only
			STATUS	current
			::= { hmWanMbusB2 66 }

hmWanMbusB2Value1E		OBJECT-TYPE
			SYNTAX	INTEGER
			MAX-ACCESS	read-only
			STATUS	current
			::= { hmWanMbusB2 67 }

hmWanMbusB2VIF1F		OBJECT-TYPE
			SYNTAX	INTEGER
			MAX-ACCESS	read-only
			STATUS	current
			::= { hmWanMbusB2 68 }

hmWanMbusB2Value1F		OBJECT-TYPE
			SYNTAX	INTEGER
			MAX-ACCESS	read-only
			STATUS	current
			::= { hmWanMbusB2 69 }

hmWanMbusB2VIF20		OBJECT-TYPE
			SYNTAX	INTEGER
			MAX-ACCESS	read-only
			STATUS	current
			::= { hmWanMbusB2 70 }

hmWanMbusB2Value20		OBJECT-TYPE
			SYNTAX	INTEGER
			MAX-ACCESS	read-only
			STATUS	current
			::= { hmWanMbusB2 71 }

hmWanMbusB2VIF21		OBJECT-TYPE
			SYNTAX	INTEGER
			MAX-ACCESS	read-only
			STATUS	current
			::= { hmWanMbusB2 72 }

hmWanMbusB2Value21		OBJECT-TYPE
			SYNTAX	INTEGER
			MAX-ACCESS	read-only
			STATUS	current
			::= { hmWanMbusB2 73 }

hmWanMbusB2VIF22		OBJECT-TYPE
			SYNTAX	INTEGER
			MAX-ACCESS	read-only
			STATUS	current
			::= { hmWanMbusB2 74 }

hmWanMbusB2Value22		OBJECT-TYPE
			SYNTAX	INTEGER
			MAX-ACCESS	read-only
			STATUS	current
			::= { hmWanMbusB2 75 }

hmWanMbusB2VIF23		OBJECT-TYPE
			SYNTAX	INTEGER
			MAX-ACCESS	read-only
			STATUS	current
			::= { hmWanMbusB2 76 }

hmWanMbusB2Value23		OBJECT-TYPE
			SYNTAX	INTEGER
			MAX-ACCESS	read-only
			STATUS	current
			::= { hmWanMbusB2 77 }

hmWanMbusB2VIF24		OBJECT-TYPE
			SYNTAX	INTEGER
			MAX-ACCESS	read-only
			STATUS	current
			::= { hmWanMbusB2 78 }

hmWanMbusB2Value24		OBJECT-TYPE
			SYNTAX	INTEGER
			MAX-ACCESS	read-only
			STATUS	current
			::= { hmWanMbusB2 79 }

hmWanMbusB2VIF25		OBJECT-TYPE
			SYNTAX	INTEGER
			MAX-ACCESS	read-only
			STATUS	current
			::= { hmWanMbusB2 80 }

hmWanMbusB2Value25		OBJECT-TYPE
			SYNTAX	INTEGER
			MAX-ACCESS	read-only
			STATUS	current
			::= { hmWanMbusB2 81 }

hmWanMbusB2VIF26		OBJECT-TYPE
			SYNTAX	INTEGER
			MAX-ACCESS	read-only
			STATUS	current
			::= { hmWanMbusB2 82 }

hmWanMbusB2Value26		OBJECT-TYPE
			SYNTAX	INTEGER
			MAX-ACCESS	read-only
			STATUS	current
			::= { hmWanMbusB2 83 }

hmWanMbusB2VIF27		OBJECT-TYPE
			SYNTAX	INTEGER
			MAX-ACCESS	read-only
			STATUS	current
			::= { hmWanMbusB2 84 }

hmWanMbusB2Value27		OBJECT-TYPE
			SYNTAX	INTEGER
			MAX-ACCESS	read-only
			STATUS	current
			::= { hmWanMbusB2 85 }

hmWanMbusB2VIF28		OBJECT-TYPE
			SYNTAX	INTEGER
			MAX-ACCESS	read-only
			STATUS	current
			::= { hmWanMbusB2 86 }

hmWanMbusB2Value28		OBJECT-TYPE
			SYNTAX	INTEGER
			MAX-ACCESS	read-only
			STATUS	current
			::= { hmWanMbusB2 87 }

hmWanMbusB2VIF29		OBJECT-TYPE
			SYNTAX	INTEGER
			MAX-ACCESS	read-only
			STATUS	current
			::= { hmWanMbusB2 88 }

hmWanMbusB2Value29		OBJECT-TYPE
			SYNTAX	INTEGER
			MAX-ACCESS	read-only
			STATUS	current
			::= { hmWanMbusB2 89 }

hmWanMbusB2VIF2A		OBJECT-TYPE
			SYNTAX	INTEGER
			MAX-ACCESS	read-only
			STATUS	current
			::= { hmWanMbusB2 90 }

hmWanMbusB2Value2A		OBJECT-TYPE
			SYNTAX	INTEGER
			MAX-ACCESS	read-only
			STATUS	current
			::= { hmWanMbusB2 91 }

hmWanMbusB2VIF2B		OBJECT-TYPE
			SYNTAX	INTEGER
			MAX-ACCESS	read-only
			STATUS	current
			::= { hmWanMbusB2 92 }

hmWanMbusB2Value2B		OBJECT-TYPE
			SYNTAX	INTEGER
			MAX-ACCESS	read-only
			STATUS	current
			::= { hmWanMbusB2 93 }

hmWanMbusB2VIF2C		OBJECT-TYPE
			SYNTAX	INTEGER
			MAX-ACCESS	read-only
			STATUS	current
			::= { hmWanMbusB2 94 }

hmWanMbusB2Value2C		OBJECT-TYPE
			SYNTAX	INTEGER
			MAX-ACCESS	read-only
			STATUS	current
			::= { hmWanMbusB2 95 }

hmWanMbusB2VIF2D		OBJECT-TYPE
			SYNTAX	INTEGER
			MAX-ACCESS	read-only
			STATUS	current
			::= { hmWanMbusB2 96 }

hmWanMbusB2Value2D		OBJECT-TYPE
			SYNTAX	INTEGER
			MAX-ACCESS	read-only
			STATUS	current
			::= { hmWanMbusB2 97 }

hmWanMbusB2VIF2E		OBJECT-TYPE
			SYNTAX	INTEGER
			MAX-ACCESS	read-only
			STATUS	current
			::= { hmWanMbusB2 98 }

hmWanMbusB2Value2E		OBJECT-TYPE
			SYNTAX	INTEGER
			MAX-ACCESS	read-only
			STATUS	current
			::= { hmWanMbusB2 99 }

hmWanMbusB2VIF2F		OBJECT-TYPE
			SYNTAX	INTEGER
			MAX-ACCESS	read-only
			STATUS	current
			::= { hmWanMbusB2 100 }

hmWanMbusB2Value2F		OBJECT-TYPE
			SYNTAX	INTEGER
			MAX-ACCESS	read-only
			STATUS	current
			::= { hmWanMbusB2 101 }

hmWanMbusB3			OBJECT IDENTIFIER ::= { hmWanMbus 179 }

hmWanMbusB3IdNumber		OBJECT-TYPE
			SYNTAX	Gauge32
			MAX-ACCESS	read-only
			STATUS	current
			::= { hmWanMbusB3 1 }

hmWanMbusB3Manufacturer	OBJECT-TYPE
			SYNTAX	Gauge32
			MAX-ACCESS	read-only
			STATUS	current
			::= { hmWanMbusB3 2 }

hmWanMbusB3Version		OBJECT-TYPE
			SYNTAX	Gauge32
			MAX-ACCESS	read-only
			STATUS	current
			::= { hmWanMbusB3 3 }

hmWanMbusB3Medium		OBJECT-TYPE
			SYNTAX	Gauge32
			MAX-ACCESS	read-only
			STATUS	current
			::= { hmWanMbusB3 4 }

hmWanMbusB3Status		OBJECT-TYPE
			SYNTAX	Gauge32
			MAX-ACCESS	read-only
			STATUS	current
			::= { hmWanMbusB3 5 }

hmWanMbusB3VIF00		OBJECT-TYPE
			SYNTAX	INTEGER
			MAX-ACCESS	read-only
			STATUS	current
			::= { hmWanMbusB3 6 }

hmWanMbusB3Value00		OBJECT-TYPE
			SYNTAX	INTEGER
			MAX-ACCESS	read-only
			STATUS	current
			::= { hmWanMbusB3 7 }

hmWanMbusB3VIF01		OBJECT-TYPE
			SYNTAX	INTEGER
			MAX-ACCESS	read-only
			STATUS	current
			::= { hmWanMbusB3 8 }

hmWanMbusB3Value01		OBJECT-TYPE
			SYNTAX	INTEGER
			MAX-ACCESS	read-only
			STATUS	current
			::= { hmWanMbusB3 9 }

hmWanMbusB3VIF02		OBJECT-TYPE
			SYNTAX	INTEGER
			MAX-ACCESS	read-only
			STATUS	current
			::= { hmWanMbusB3 10 }

hmWanMbusB3Value02		OBJECT-TYPE
			SYNTAX	INTEGER
			MAX-ACCESS	read-only
			STATUS	current
			::= { hmWanMbusB3 11 }

hmWanMbusB3VIF03		OBJECT-TYPE
			SYNTAX	INTEGER
			MAX-ACCESS	read-only
			STATUS	current
			::= { hmWanMbusB3 12 }

hmWanMbusB3Value03		OBJECT-TYPE
			SYNTAX	INTEGER
			MAX-ACCESS	read-only
			STATUS	current
			::= { hmWanMbusB3 13 }

hmWanMbusB3VIF04		OBJECT-TYPE
			SYNTAX	INTEGER
			MAX-ACCESS	read-only
			STATUS	current
			::= { hmWanMbusB3 14 }

hmWanMbusB3Value04		OBJECT-TYPE
			SYNTAX	INTEGER
			MAX-ACCESS	read-only
			STATUS	current
			::= { hmWanMbusB3 15 }

hmWanMbusB3VIF05		OBJECT-TYPE
			SYNTAX	INTEGER
			MAX-ACCESS	read-only
			STATUS	current
			::= { hmWanMbusB3 16 }

hmWanMbusB3Value05		OBJECT-TYPE
			SYNTAX	INTEGER
			MAX-ACCESS	read-only
			STATUS	current
			::= { hmWanMbusB3 17 }

hmWanMbusB3VIF06		OBJECT-TYPE
			SYNTAX	INTEGER
			MAX-ACCESS	read-only
			STATUS	current
			::= { hmWanMbusB3 18 }

hmWanMbusB3Value06		OBJECT-TYPE
			SYNTAX	INTEGER
			MAX-ACCESS	read-only
			STATUS	current
			::= { hmWanMbusB3 19 }

hmWanMbusB3VIF07		OBJECT-TYPE
			SYNTAX	INTEGER
			MAX-ACCESS	read-only
			STATUS	current
			::= { hmWanMbusB3 20 }

hmWanMbusB3Value07		OBJECT-TYPE
			SYNTAX	INTEGER
			MAX-ACCESS	read-only
			STATUS	current
			::= { hmWanMbusB3 21 }

hmWanMbusB3VIF08		OBJECT-TYPE
			SYNTAX	INTEGER
			MAX-ACCESS	read-only
			STATUS	current
			::= { hmWanMbusB3 22 }

hmWanMbusB3Value08		OBJECT-TYPE
			SYNTAX	INTEGER
			MAX-ACCESS	read-only
			STATUS	current
			::= { hmWanMbusB3 23 }

hmWanMbusB3VIF09		OBJECT-TYPE
			SYNTAX	INTEGER
			MAX-ACCESS	read-only
			STATUS	current
			::= { hmWanMbusB3 24 }

hmWanMbusB3Value09		OBJECT-TYPE
			SYNTAX	INTEGER
			MAX-ACCESS	read-only
			STATUS	current
			::= { hmWanMbusB3 25 }

hmWanMbusB3VIF0A		OBJECT-TYPE
			SYNTAX	INTEGER
			MAX-ACCESS	read-only
			STATUS	current
			::= { hmWanMbusB3 26 }

hmWanMbusB3Value0A		OBJECT-TYPE
			SYNTAX	INTEGER
			MAX-ACCESS	read-only
			STATUS	current
			::= { hmWanMbusB3 27 }

hmWanMbusB3VIF0B		OBJECT-TYPE
			SYNTAX	INTEGER
			MAX-ACCESS	read-only
			STATUS	current
			::= { hmWanMbusB3 28 }

hmWanMbusB3Value0B		OBJECT-TYPE
			SYNTAX	INTEGER
			MAX-ACCESS	read-only
			STATUS	current
			::= { hmWanMbusB3 29 }

hmWanMbusB3VIF0C		OBJECT-TYPE
			SYNTAX	INTEGER
			MAX-ACCESS	read-only
			STATUS	current
			::= { hmWanMbusB3 30 }

hmWanMbusB3Value0C		OBJECT-TYPE
			SYNTAX	INTEGER
			MAX-ACCESS	read-only
			STATUS	current
			::= { hmWanMbusB3 31 }

hmWanMbusB3VIF0D		OBJECT-TYPE
			SYNTAX	INTEGER
			MAX-ACCESS	read-only
			STATUS	current
			::= { hmWanMbusB3 32 }

hmWanMbusB3Value0D		OBJECT-TYPE
			SYNTAX	INTEGER
			MAX-ACCESS	read-only
			STATUS	current
			::= { hmWanMbusB3 33 }

hmWanMbusB3VIF0E		OBJECT-TYPE
			SYNTAX	INTEGER
			MAX-ACCESS	read-only
			STATUS	current
			::= { hmWanMbusB3 34 }

hmWanMbusB3Value0E		OBJECT-TYPE
			SYNTAX	INTEGER
			MAX-ACCESS	read-only
			STATUS	current
			::= { hmWanMbusB3 35 }

hmWanMbusB3VIF0F		OBJECT-TYPE
			SYNTAX	INTEGER
			MAX-ACCESS	read-only
			STATUS	current
			::= { hmWanMbusB3 36 }

hmWanMbusB3Value0F		OBJECT-TYPE
			SYNTAX	INTEGER
			MAX-ACCESS	read-only
			STATUS	current
			::= { hmWanMbusB3 37 }

hmWanMbusB3VIF10		OBJECT-TYPE
			SYNTAX	INTEGER
			MAX-ACCESS	read-only
			STATUS	current
			::= { hmWanMbusB3 38 }

hmWanMbusB3Value10		OBJECT-TYPE
			SYNTAX	INTEGER
			MAX-ACCESS	read-only
			STATUS	current
			::= { hmWanMbusB3 39 }

hmWanMbusB3VIF11		OBJECT-TYPE
			SYNTAX	INTEGER
			MAX-ACCESS	read-only
			STATUS	current
			::= { hmWanMbusB3 40 }

hmWanMbusB3Value11		OBJECT-TYPE
			SYNTAX	INTEGER
			MAX-ACCESS	read-only
			STATUS	current
			::= { hmWanMbusB3 41 }

hmWanMbusB3VIF12		OBJECT-TYPE
			SYNTAX	INTEGER
			MAX-ACCESS	read-only
			STATUS	current
			::= { hmWanMbusB3 42 }

hmWanMbusB3Value12		OBJECT-TYPE
			SYNTAX	INTEGER
			MAX-ACCESS	read-only
			STATUS	current
			::= { hmWanMbusB3 43 }

hmWanMbusB3VIF13		OBJECT-TYPE
			SYNTAX	INTEGER
			MAX-ACCESS	read-only
			STATUS	current
			::= { hmWanMbusB3 44 }

hmWanMbusB3Value13		OBJECT-TYPE
			SYNTAX	INTEGER
			MAX-ACCESS	read-only
			STATUS	current
			::= { hmWanMbusB3 45 }

hmWanMbusB3VIF14		OBJECT-TYPE
			SYNTAX	INTEGER
			MAX-ACCESS	read-only
			STATUS	current
			::= { hmWanMbusB3 46 }

hmWanMbusB3Value14		OBJECT-TYPE
			SYNTAX	INTEGER
			MAX-ACCESS	read-only
			STATUS	current
			::= { hmWanMbusB3 47 }

hmWanMbusB3VIF15		OBJECT-TYPE
			SYNTAX	INTEGER
			MAX-ACCESS	read-only
			STATUS	current
			::= { hmWanMbusB3 48 }

hmWanMbusB3Value15		OBJECT-TYPE
			SYNTAX	INTEGER
			MAX-ACCESS	read-only
			STATUS	current
			::= { hmWanMbusB3 49 }

hmWanMbusB3VIF16		OBJECT-TYPE
			SYNTAX	INTEGER
			MAX-ACCESS	read-only
			STATUS	current
			::= { hmWanMbusB3 50 }

hmWanMbusB3Value16		OBJECT-TYPE
			SYNTAX	INTEGER
			MAX-ACCESS	read-only
			STATUS	current
			::= { hmWanMbusB3 51 }

hmWanMbusB3VIF17		OBJECT-TYPE
			SYNTAX	INTEGER
			MAX-ACCESS	read-only
			STATUS	current
			::= { hmWanMbusB3 52 }

hmWanMbusB3Value17		OBJECT-TYPE
			SYNTAX	INTEGER
			MAX-ACCESS	read-only
			STATUS	current
			::= { hmWanMbusB3 53 }

hmWanMbusB3VIF18		OBJECT-TYPE
			SYNTAX	INTEGER
			MAX-ACCESS	read-only
			STATUS	current
			::= { hmWanMbusB3 54 }

hmWanMbusB3Value18		OBJECT-TYPE
			SYNTAX	INTEGER
			MAX-ACCESS	read-only
			STATUS	current
			::= { hmWanMbusB3 55 }

hmWanMbusB3VIF19		OBJECT-TYPE
			SYNTAX	INTEGER
			MAX-ACCESS	read-only
			STATUS	current
			::= { hmWanMbusB3 56 }

hmWanMbusB3Value19		OBJECT-TYPE
			SYNTAX	INTEGER
			MAX-ACCESS	read-only
			STATUS	current
			::= { hmWanMbusB3 57 }

hmWanMbusB3VIF1A		OBJECT-TYPE
			SYNTAX	INTEGER
			MAX-ACCESS	read-only
			STATUS	current
			::= { hmWanMbusB3 58 }

hmWanMbusB3Value1A		OBJECT-TYPE
			SYNTAX	INTEGER
			MAX-ACCESS	read-only
			STATUS	current
			::= { hmWanMbusB3 59 }

hmWanMbusB3VIF1B		OBJECT-TYPE
			SYNTAX	INTEGER
			MAX-ACCESS	read-only
			STATUS	current
			::= { hmWanMbusB3 60 }

hmWanMbusB3Value1B		OBJECT-TYPE
			SYNTAX	INTEGER
			MAX-ACCESS	read-only
			STATUS	current
			::= { hmWanMbusB3 61 }

hmWanMbusB3VIF1C		OBJECT-TYPE
			SYNTAX	INTEGER
			MAX-ACCESS	read-only
			STATUS	current
			::= { hmWanMbusB3 62 }

hmWanMbusB3Value1C		OBJECT-TYPE
			SYNTAX	INTEGER
			MAX-ACCESS	read-only
			STATUS	current
			::= { hmWanMbusB3 63 }

hmWanMbusB3VIF1D		OBJECT-TYPE
			SYNTAX	INTEGER
			MAX-ACCESS	read-only
			STATUS	current
			::= { hmWanMbusB3 64 }

hmWanMbusB3Value1D		OBJECT-TYPE
			SYNTAX	INTEGER
			MAX-ACCESS	read-only
			STATUS	current
			::= { hmWanMbusB3 65 }

hmWanMbusB3VIF1E		OBJECT-TYPE
			SYNTAX	INTEGER
			MAX-ACCESS	read-only
			STATUS	current
			::= { hmWanMbusB3 66 }

hmWanMbusB3Value1E		OBJECT-TYPE
			SYNTAX	INTEGER
			MAX-ACCESS	read-only
			STATUS	current
			::= { hmWanMbusB3 67 }

hmWanMbusB3VIF1F		OBJECT-TYPE
			SYNTAX	INTEGER
			MAX-ACCESS	read-only
			STATUS	current
			::= { hmWanMbusB3 68 }

hmWanMbusB3Value1F		OBJECT-TYPE
			SYNTAX	INTEGER
			MAX-ACCESS	read-only
			STATUS	current
			::= { hmWanMbusB3 69 }

hmWanMbusB3VIF20		OBJECT-TYPE
			SYNTAX	INTEGER
			MAX-ACCESS	read-only
			STATUS	current
			::= { hmWanMbusB3 70 }

hmWanMbusB3Value20		OBJECT-TYPE
			SYNTAX	INTEGER
			MAX-ACCESS	read-only
			STATUS	current
			::= { hmWanMbusB3 71 }

hmWanMbusB3VIF21		OBJECT-TYPE
			SYNTAX	INTEGER
			MAX-ACCESS	read-only
			STATUS	current
			::= { hmWanMbusB3 72 }

hmWanMbusB3Value21		OBJECT-TYPE
			SYNTAX	INTEGER
			MAX-ACCESS	read-only
			STATUS	current
			::= { hmWanMbusB3 73 }

hmWanMbusB3VIF22		OBJECT-TYPE
			SYNTAX	INTEGER
			MAX-ACCESS	read-only
			STATUS	current
			::= { hmWanMbusB3 74 }

hmWanMbusB3Value22		OBJECT-TYPE
			SYNTAX	INTEGER
			MAX-ACCESS	read-only
			STATUS	current
			::= { hmWanMbusB3 75 }

hmWanMbusB3VIF23		OBJECT-TYPE
			SYNTAX	INTEGER
			MAX-ACCESS	read-only
			STATUS	current
			::= { hmWanMbusB3 76 }

hmWanMbusB3Value23		OBJECT-TYPE
			SYNTAX	INTEGER
			MAX-ACCESS	read-only
			STATUS	current
			::= { hmWanMbusB3 77 }

hmWanMbusB3VIF24		OBJECT-TYPE
			SYNTAX	INTEGER
			MAX-ACCESS	read-only
			STATUS	current
			::= { hmWanMbusB3 78 }

hmWanMbusB3Value24		OBJECT-TYPE
			SYNTAX	INTEGER
			MAX-ACCESS	read-only
			STATUS	current
			::= { hmWanMbusB3 79 }

hmWanMbusB3VIF25		OBJECT-TYPE
			SYNTAX	INTEGER
			MAX-ACCESS	read-only
			STATUS	current
			::= { hmWanMbusB3 80 }

hmWanMbusB3Value25		OBJECT-TYPE
			SYNTAX	INTEGER
			MAX-ACCESS	read-only
			STATUS	current
			::= { hmWanMbusB3 81 }

hmWanMbusB3VIF26		OBJECT-TYPE
			SYNTAX	INTEGER
			MAX-ACCESS	read-only
			STATUS	current
			::= { hmWanMbusB3 82 }

hmWanMbusB3Value26		OBJECT-TYPE
			SYNTAX	INTEGER
			MAX-ACCESS	read-only
			STATUS	current
			::= { hmWanMbusB3 83 }

hmWanMbusB3VIF27		OBJECT-TYPE
			SYNTAX	INTEGER
			MAX-ACCESS	read-only
			STATUS	current
			::= { hmWanMbusB3 84 }

hmWanMbusB3Value27		OBJECT-TYPE
			SYNTAX	INTEGER
			MAX-ACCESS	read-only
			STATUS	current
			::= { hmWanMbusB3 85 }

hmWanMbusB3VIF28		OBJECT-TYPE
			SYNTAX	INTEGER
			MAX-ACCESS	read-only
			STATUS	current
			::= { hmWanMbusB3 86 }

hmWanMbusB3Value28		OBJECT-TYPE
			SYNTAX	INTEGER
			MAX-ACCESS	read-only
			STATUS	current
			::= { hmWanMbusB3 87 }

hmWanMbusB3VIF29		OBJECT-TYPE
			SYNTAX	INTEGER
			MAX-ACCESS	read-only
			STATUS	current
			::= { hmWanMbusB3 88 }

hmWanMbusB3Value29		OBJECT-TYPE
			SYNTAX	INTEGER
			MAX-ACCESS	read-only
			STATUS	current
			::= { hmWanMbusB3 89 }

hmWanMbusB3VIF2A		OBJECT-TYPE
			SYNTAX	INTEGER
			MAX-ACCESS	read-only
			STATUS	current
			::= { hmWanMbusB3 90 }

hmWanMbusB3Value2A		OBJECT-TYPE
			SYNTAX	INTEGER
			MAX-ACCESS	read-only
			STATUS	current
			::= { hmWanMbusB3 91 }

hmWanMbusB3VIF2B		OBJECT-TYPE
			SYNTAX	INTEGER
			MAX-ACCESS	read-only
			STATUS	current
			::= { hmWanMbusB3 92 }

hmWanMbusB3Value2B		OBJECT-TYPE
			SYNTAX	INTEGER
			MAX-ACCESS	read-only
			STATUS	current
			::= { hmWanMbusB3 93 }

hmWanMbusB3VIF2C		OBJECT-TYPE
			SYNTAX	INTEGER
			MAX-ACCESS	read-only
			STATUS	current
			::= { hmWanMbusB3 94 }

hmWanMbusB3Value2C		OBJECT-TYPE
			SYNTAX	INTEGER
			MAX-ACCESS	read-only
			STATUS	current
			::= { hmWanMbusB3 95 }

hmWanMbusB3VIF2D		OBJECT-TYPE
			SYNTAX	INTEGER
			MAX-ACCESS	read-only
			STATUS	current
			::= { hmWanMbusB3 96 }

hmWanMbusB3Value2D		OBJECT-TYPE
			SYNTAX	INTEGER
			MAX-ACCESS	read-only
			STATUS	current
			::= { hmWanMbusB3 97 }

hmWanMbusB3VIF2E		OBJECT-TYPE
			SYNTAX	INTEGER
			MAX-ACCESS	read-only
			STATUS	current
			::= { hmWanMbusB3 98 }

hmWanMbusB3Value2E		OBJECT-TYPE
			SYNTAX	INTEGER
			MAX-ACCESS	read-only
			STATUS	current
			::= { hmWanMbusB3 99 }

hmWanMbusB3VIF2F		OBJECT-TYPE
			SYNTAX	INTEGER
			MAX-ACCESS	read-only
			STATUS	current
			::= { hmWanMbusB3 100 }

hmWanMbusB3Value2F		OBJECT-TYPE
			SYNTAX	INTEGER
			MAX-ACCESS	read-only
			STATUS	current
			::= { hmWanMbusB3 101 }

hmWanMbusB4			OBJECT IDENTIFIER ::= { hmWanMbus 180 }

hmWanMbusB4IdNumber		OBJECT-TYPE
			SYNTAX	Gauge32
			MAX-ACCESS	read-only
			STATUS	current
			::= { hmWanMbusB4 1 }

hmWanMbusB4Manufacturer	OBJECT-TYPE
			SYNTAX	Gauge32
			MAX-ACCESS	read-only
			STATUS	current
			::= { hmWanMbusB4 2 }

hmWanMbusB4Version		OBJECT-TYPE
			SYNTAX	Gauge32
			MAX-ACCESS	read-only
			STATUS	current
			::= { hmWanMbusB4 3 }

hmWanMbusB4Medium		OBJECT-TYPE
			SYNTAX	Gauge32
			MAX-ACCESS	read-only
			STATUS	current
			::= { hmWanMbusB4 4 }

hmWanMbusB4Status		OBJECT-TYPE
			SYNTAX	Gauge32
			MAX-ACCESS	read-only
			STATUS	current
			::= { hmWanMbusB4 5 }

hmWanMbusB4VIF00		OBJECT-TYPE
			SYNTAX	INTEGER
			MAX-ACCESS	read-only
			STATUS	current
			::= { hmWanMbusB4 6 }

hmWanMbusB4Value00		OBJECT-TYPE
			SYNTAX	INTEGER
			MAX-ACCESS	read-only
			STATUS	current
			::= { hmWanMbusB4 7 }

hmWanMbusB4VIF01		OBJECT-TYPE
			SYNTAX	INTEGER
			MAX-ACCESS	read-only
			STATUS	current
			::= { hmWanMbusB4 8 }

hmWanMbusB4Value01		OBJECT-TYPE
			SYNTAX	INTEGER
			MAX-ACCESS	read-only
			STATUS	current
			::= { hmWanMbusB4 9 }

hmWanMbusB4VIF02		OBJECT-TYPE
			SYNTAX	INTEGER
			MAX-ACCESS	read-only
			STATUS	current
			::= { hmWanMbusB4 10 }

hmWanMbusB4Value02		OBJECT-TYPE
			SYNTAX	INTEGER
			MAX-ACCESS	read-only
			STATUS	current
			::= { hmWanMbusB4 11 }

hmWanMbusB4VIF03		OBJECT-TYPE
			SYNTAX	INTEGER
			MAX-ACCESS	read-only
			STATUS	current
			::= { hmWanMbusB4 12 }

hmWanMbusB4Value03		OBJECT-TYPE
			SYNTAX	INTEGER
			MAX-ACCESS	read-only
			STATUS	current
			::= { hmWanMbusB4 13 }

hmWanMbusB4VIF04		OBJECT-TYPE
			SYNTAX	INTEGER
			MAX-ACCESS	read-only
			STATUS	current
			::= { hmWanMbusB4 14 }

hmWanMbusB4Value04		OBJECT-TYPE
			SYNTAX	INTEGER
			MAX-ACCESS	read-only
			STATUS	current
			::= { hmWanMbusB4 15 }

hmWanMbusB4VIF05		OBJECT-TYPE
			SYNTAX	INTEGER
			MAX-ACCESS	read-only
			STATUS	current
			::= { hmWanMbusB4 16 }

hmWanMbusB4Value05		OBJECT-TYPE
			SYNTAX	INTEGER
			MAX-ACCESS	read-only
			STATUS	current
			::= { hmWanMbusB4 17 }

hmWanMbusB4VIF06		OBJECT-TYPE
			SYNTAX	INTEGER
			MAX-ACCESS	read-only
			STATUS	current
			::= { hmWanMbusB4 18 }

hmWanMbusB4Value06		OBJECT-TYPE
			SYNTAX	INTEGER
			MAX-ACCESS	read-only
			STATUS	current
			::= { hmWanMbusB4 19 }

hmWanMbusB4VIF07		OBJECT-TYPE
			SYNTAX	INTEGER
			MAX-ACCESS	read-only
			STATUS	current
			::= { hmWanMbusB4 20 }

hmWanMbusB4Value07		OBJECT-TYPE
			SYNTAX	INTEGER
			MAX-ACCESS	read-only
			STATUS	current
			::= { hmWanMbusB4 21 }

hmWanMbusB4VIF08		OBJECT-TYPE
			SYNTAX	INTEGER
			MAX-ACCESS	read-only
			STATUS	current
			::= { hmWanMbusB4 22 }

hmWanMbusB4Value08		OBJECT-TYPE
			SYNTAX	INTEGER
			MAX-ACCESS	read-only
			STATUS	current
			::= { hmWanMbusB4 23 }

hmWanMbusB4VIF09		OBJECT-TYPE
			SYNTAX	INTEGER
			MAX-ACCESS	read-only
			STATUS	current
			::= { hmWanMbusB4 24 }

hmWanMbusB4Value09		OBJECT-TYPE
			SYNTAX	INTEGER
			MAX-ACCESS	read-only
			STATUS	current
			::= { hmWanMbusB4 25 }

hmWanMbusB4VIF0A		OBJECT-TYPE
			SYNTAX	INTEGER
			MAX-ACCESS	read-only
			STATUS	current
			::= { hmWanMbusB4 26 }

hmWanMbusB4Value0A		OBJECT-TYPE
			SYNTAX	INTEGER
			MAX-ACCESS	read-only
			STATUS	current
			::= { hmWanMbusB4 27 }

hmWanMbusB4VIF0B		OBJECT-TYPE
			SYNTAX	INTEGER
			MAX-ACCESS	read-only
			STATUS	current
			::= { hmWanMbusB4 28 }

hmWanMbusB4Value0B		OBJECT-TYPE
			SYNTAX	INTEGER
			MAX-ACCESS	read-only
			STATUS	current
			::= { hmWanMbusB4 29 }

hmWanMbusB4VIF0C		OBJECT-TYPE
			SYNTAX	INTEGER
			MAX-ACCESS	read-only
			STATUS	current
			::= { hmWanMbusB4 30 }

hmWanMbusB4Value0C		OBJECT-TYPE
			SYNTAX	INTEGER
			MAX-ACCESS	read-only
			STATUS	current
			::= { hmWanMbusB4 31 }

hmWanMbusB4VIF0D		OBJECT-TYPE
			SYNTAX	INTEGER
			MAX-ACCESS	read-only
			STATUS	current
			::= { hmWanMbusB4 32 }

hmWanMbusB4Value0D		OBJECT-TYPE
			SYNTAX	INTEGER
			MAX-ACCESS	read-only
			STATUS	current
			::= { hmWanMbusB4 33 }

hmWanMbusB4VIF0E		OBJECT-TYPE
			SYNTAX	INTEGER
			MAX-ACCESS	read-only
			STATUS	current
			::= { hmWanMbusB4 34 }

hmWanMbusB4Value0E		OBJECT-TYPE
			SYNTAX	INTEGER
			MAX-ACCESS	read-only
			STATUS	current
			::= { hmWanMbusB4 35 }

hmWanMbusB4VIF0F		OBJECT-TYPE
			SYNTAX	INTEGER
			MAX-ACCESS	read-only
			STATUS	current
			::= { hmWanMbusB4 36 }

hmWanMbusB4Value0F		OBJECT-TYPE
			SYNTAX	INTEGER
			MAX-ACCESS	read-only
			STATUS	current
			::= { hmWanMbusB4 37 }

hmWanMbusB4VIF10		OBJECT-TYPE
			SYNTAX	INTEGER
			MAX-ACCESS	read-only
			STATUS	current
			::= { hmWanMbusB4 38 }

hmWanMbusB4Value10		OBJECT-TYPE
			SYNTAX	INTEGER
			MAX-ACCESS	read-only
			STATUS	current
			::= { hmWanMbusB4 39 }

hmWanMbusB4VIF11		OBJECT-TYPE
			SYNTAX	INTEGER
			MAX-ACCESS	read-only
			STATUS	current
			::= { hmWanMbusB4 40 }

hmWanMbusB4Value11		OBJECT-TYPE
			SYNTAX	INTEGER
			MAX-ACCESS	read-only
			STATUS	current
			::= { hmWanMbusB4 41 }

hmWanMbusB4VIF12		OBJECT-TYPE
			SYNTAX	INTEGER
			MAX-ACCESS	read-only
			STATUS	current
			::= { hmWanMbusB4 42 }

hmWanMbusB4Value12		OBJECT-TYPE
			SYNTAX	INTEGER
			MAX-ACCESS	read-only
			STATUS	current
			::= { hmWanMbusB4 43 }

hmWanMbusB4VIF13		OBJECT-TYPE
			SYNTAX	INTEGER
			MAX-ACCESS	read-only
			STATUS	current
			::= { hmWanMbusB4 44 }

hmWanMbusB4Value13		OBJECT-TYPE
			SYNTAX	INTEGER
			MAX-ACCESS	read-only
			STATUS	current
			::= { hmWanMbusB4 45 }

hmWanMbusB4VIF14		OBJECT-TYPE
			SYNTAX	INTEGER
			MAX-ACCESS	read-only
			STATUS	current
			::= { hmWanMbusB4 46 }

hmWanMbusB4Value14		OBJECT-TYPE
			SYNTAX	INTEGER
			MAX-ACCESS	read-only
			STATUS	current
			::= { hmWanMbusB4 47 }

hmWanMbusB4VIF15		OBJECT-TYPE
			SYNTAX	INTEGER
			MAX-ACCESS	read-only
			STATUS	current
			::= { hmWanMbusB4 48 }

hmWanMbusB4Value15		OBJECT-TYPE
			SYNTAX	INTEGER
			MAX-ACCESS	read-only
			STATUS	current
			::= { hmWanMbusB4 49 }

hmWanMbusB4VIF16		OBJECT-TYPE
			SYNTAX	INTEGER
			MAX-ACCESS	read-only
			STATUS	current
			::= { hmWanMbusB4 50 }

hmWanMbusB4Value16		OBJECT-TYPE
			SYNTAX	INTEGER
			MAX-ACCESS	read-only
			STATUS	current
			::= { hmWanMbusB4 51 }

hmWanMbusB4VIF17		OBJECT-TYPE
			SYNTAX	INTEGER
			MAX-ACCESS	read-only
			STATUS	current
			::= { hmWanMbusB4 52 }

hmWanMbusB4Value17		OBJECT-TYPE
			SYNTAX	INTEGER
			MAX-ACCESS	read-only
			STATUS	current
			::= { hmWanMbusB4 53 }

hmWanMbusB4VIF18		OBJECT-TYPE
			SYNTAX	INTEGER
			MAX-ACCESS	read-only
			STATUS	current
			::= { hmWanMbusB4 54 }

hmWanMbusB4Value18		OBJECT-TYPE
			SYNTAX	INTEGER
			MAX-ACCESS	read-only
			STATUS	current
			::= { hmWanMbusB4 55 }

hmWanMbusB4VIF19		OBJECT-TYPE
			SYNTAX	INTEGER
			MAX-ACCESS	read-only
			STATUS	current
			::= { hmWanMbusB4 56 }

hmWanMbusB4Value19		OBJECT-TYPE
			SYNTAX	INTEGER
			MAX-ACCESS	read-only
			STATUS	current
			::= { hmWanMbusB4 57 }

hmWanMbusB4VIF1A		OBJECT-TYPE
			SYNTAX	INTEGER
			MAX-ACCESS	read-only
			STATUS	current
			::= { hmWanMbusB4 58 }

hmWanMbusB4Value1A		OBJECT-TYPE
			SYNTAX	INTEGER
			MAX-ACCESS	read-only
			STATUS	current
			::= { hmWanMbusB4 59 }

hmWanMbusB4VIF1B		OBJECT-TYPE
			SYNTAX	INTEGER
			MAX-ACCESS	read-only
			STATUS	current
			::= { hmWanMbusB4 60 }

hmWanMbusB4Value1B		OBJECT-TYPE
			SYNTAX	INTEGER
			MAX-ACCESS	read-only
			STATUS	current
			::= { hmWanMbusB4 61 }

hmWanMbusB4VIF1C		OBJECT-TYPE
			SYNTAX	INTEGER
			MAX-ACCESS	read-only
			STATUS	current
			::= { hmWanMbusB4 62 }

hmWanMbusB4Value1C		OBJECT-TYPE
			SYNTAX	INTEGER
			MAX-ACCESS	read-only
			STATUS	current
			::= { hmWanMbusB4 63 }

hmWanMbusB4VIF1D		OBJECT-TYPE
			SYNTAX	INTEGER
			MAX-ACCESS	read-only
			STATUS	current
			::= { hmWanMbusB4 64 }

hmWanMbusB4Value1D		OBJECT-TYPE
			SYNTAX	INTEGER
			MAX-ACCESS	read-only
			STATUS	current
			::= { hmWanMbusB4 65 }

hmWanMbusB4VIF1E		OBJECT-TYPE
			SYNTAX	INTEGER
			MAX-ACCESS	read-only
			STATUS	current
			::= { hmWanMbusB4 66 }

hmWanMbusB4Value1E		OBJECT-TYPE
			SYNTAX	INTEGER
			MAX-ACCESS	read-only
			STATUS	current
			::= { hmWanMbusB4 67 }

hmWanMbusB4VIF1F		OBJECT-TYPE
			SYNTAX	INTEGER
			MAX-ACCESS	read-only
			STATUS	current
			::= { hmWanMbusB4 68 }

hmWanMbusB4Value1F		OBJECT-TYPE
			SYNTAX	INTEGER
			MAX-ACCESS	read-only
			STATUS	current
			::= { hmWanMbusB4 69 }

hmWanMbusB4VIF20		OBJECT-TYPE
			SYNTAX	INTEGER
			MAX-ACCESS	read-only
			STATUS	current
			::= { hmWanMbusB4 70 }

hmWanMbusB4Value20		OBJECT-TYPE
			SYNTAX	INTEGER
			MAX-ACCESS	read-only
			STATUS	current
			::= { hmWanMbusB4 71 }

hmWanMbusB4VIF21		OBJECT-TYPE
			SYNTAX	INTEGER
			MAX-ACCESS	read-only
			STATUS	current
			::= { hmWanMbusB4 72 }

hmWanMbusB4Value21		OBJECT-TYPE
			SYNTAX	INTEGER
			MAX-ACCESS	read-only
			STATUS	current
			::= { hmWanMbusB4 73 }

hmWanMbusB4VIF22		OBJECT-TYPE
			SYNTAX	INTEGER
			MAX-ACCESS	read-only
			STATUS	current
			::= { hmWanMbusB4 74 }

hmWanMbusB4Value22		OBJECT-TYPE
			SYNTAX	INTEGER
			MAX-ACCESS	read-only
			STATUS	current
			::= { hmWanMbusB4 75 }

hmWanMbusB4VIF23		OBJECT-TYPE
			SYNTAX	INTEGER
			MAX-ACCESS	read-only
			STATUS	current
			::= { hmWanMbusB4 76 }

hmWanMbusB4Value23		OBJECT-TYPE
			SYNTAX	INTEGER
			MAX-ACCESS	read-only
			STATUS	current
			::= { hmWanMbusB4 77 }

hmWanMbusB4VIF24		OBJECT-TYPE
			SYNTAX	INTEGER
			MAX-ACCESS	read-only
			STATUS	current
			::= { hmWanMbusB4 78 }

hmWanMbusB4Value24		OBJECT-TYPE
			SYNTAX	INTEGER
			MAX-ACCESS	read-only
			STATUS	current
			::= { hmWanMbusB4 79 }

hmWanMbusB4VIF25		OBJECT-TYPE
			SYNTAX	INTEGER
			MAX-ACCESS	read-only
			STATUS	current
			::= { hmWanMbusB4 80 }

hmWanMbusB4Value25		OBJECT-TYPE
			SYNTAX	INTEGER
			MAX-ACCESS	read-only
			STATUS	current
			::= { hmWanMbusB4 81 }

hmWanMbusB4VIF26		OBJECT-TYPE
			SYNTAX	INTEGER
			MAX-ACCESS	read-only
			STATUS	current
			::= { hmWanMbusB4 82 }

hmWanMbusB4Value26		OBJECT-TYPE
			SYNTAX	INTEGER
			MAX-ACCESS	read-only
			STATUS	current
			::= { hmWanMbusB4 83 }

hmWanMbusB4VIF27		OBJECT-TYPE
			SYNTAX	INTEGER
			MAX-ACCESS	read-only
			STATUS	current
			::= { hmWanMbusB4 84 }

hmWanMbusB4Value27		OBJECT-TYPE
			SYNTAX	INTEGER
			MAX-ACCESS	read-only
			STATUS	current
			::= { hmWanMbusB4 85 }

hmWanMbusB4VIF28		OBJECT-TYPE
			SYNTAX	INTEGER
			MAX-ACCESS	read-only
			STATUS	current
			::= { hmWanMbusB4 86 }

hmWanMbusB4Value28		OBJECT-TYPE
			SYNTAX	INTEGER
			MAX-ACCESS	read-only
			STATUS	current
			::= { hmWanMbusB4 87 }

hmWanMbusB4VIF29		OBJECT-TYPE
			SYNTAX	INTEGER
			MAX-ACCESS	read-only
			STATUS	current
			::= { hmWanMbusB4 88 }

hmWanMbusB4Value29		OBJECT-TYPE
			SYNTAX	INTEGER
			MAX-ACCESS	read-only
			STATUS	current
			::= { hmWanMbusB4 89 }

hmWanMbusB4VIF2A		OBJECT-TYPE
			SYNTAX	INTEGER
			MAX-ACCESS	read-only
			STATUS	current
			::= { hmWanMbusB4 90 }

hmWanMbusB4Value2A		OBJECT-TYPE
			SYNTAX	INTEGER
			MAX-ACCESS	read-only
			STATUS	current
			::= { hmWanMbusB4 91 }

hmWanMbusB4VIF2B		OBJECT-TYPE
			SYNTAX	INTEGER
			MAX-ACCESS	read-only
			STATUS	current
			::= { hmWanMbusB4 92 }

hmWanMbusB4Value2B		OBJECT-TYPE
			SYNTAX	INTEGER
			MAX-ACCESS	read-only
			STATUS	current
			::= { hmWanMbusB4 93 }

hmWanMbusB4VIF2C		OBJECT-TYPE
			SYNTAX	INTEGER
			MAX-ACCESS	read-only
			STATUS	current
			::= { hmWanMbusB4 94 }

hmWanMbusB4Value2C		OBJECT-TYPE
			SYNTAX	INTEGER
			MAX-ACCESS	read-only
			STATUS	current
			::= { hmWanMbusB4 95 }

hmWanMbusB4VIF2D		OBJECT-TYPE
			SYNTAX	INTEGER
			MAX-ACCESS	read-only
			STATUS	current
			::= { hmWanMbusB4 96 }

hmWanMbusB4Value2D		OBJECT-TYPE
			SYNTAX	INTEGER
			MAX-ACCESS	read-only
			STATUS	current
			::= { hmWanMbusB4 97 }

hmWanMbusB4VIF2E		OBJECT-TYPE
			SYNTAX	INTEGER
			MAX-ACCESS	read-only
			STATUS	current
			::= { hmWanMbusB4 98 }

hmWanMbusB4Value2E		OBJECT-TYPE
			SYNTAX	INTEGER
			MAX-ACCESS	read-only
			STATUS	current
			::= { hmWanMbusB4 99 }

hmWanMbusB4VIF2F		OBJECT-TYPE
			SYNTAX	INTEGER
			MAX-ACCESS	read-only
			STATUS	current
			::= { hmWanMbusB4 100 }

hmWanMbusB4Value2F		OBJECT-TYPE
			SYNTAX	INTEGER
			MAX-ACCESS	read-only
			STATUS	current
			::= { hmWanMbusB4 101 }

hmWanMbusB5			OBJECT IDENTIFIER ::= { hmWanMbus 181 }

hmWanMbusB5IdNumber		OBJECT-TYPE
			SYNTAX	Gauge32
			MAX-ACCESS	read-only
			STATUS	current
			::= { hmWanMbusB5 1 }

hmWanMbusB5Manufacturer	OBJECT-TYPE
			SYNTAX	Gauge32
			MAX-ACCESS	read-only
			STATUS	current
			::= { hmWanMbusB5 2 }

hmWanMbusB5Version		OBJECT-TYPE
			SYNTAX	Gauge32
			MAX-ACCESS	read-only
			STATUS	current
			::= { hmWanMbusB5 3 }

hmWanMbusB5Medium		OBJECT-TYPE
			SYNTAX	Gauge32
			MAX-ACCESS	read-only
			STATUS	current
			::= { hmWanMbusB5 4 }

hmWanMbusB5Status		OBJECT-TYPE
			SYNTAX	Gauge32
			MAX-ACCESS	read-only
			STATUS	current
			::= { hmWanMbusB5 5 }

hmWanMbusB5VIF00		OBJECT-TYPE
			SYNTAX	INTEGER
			MAX-ACCESS	read-only
			STATUS	current
			::= { hmWanMbusB5 6 }

hmWanMbusB5Value00		OBJECT-TYPE
			SYNTAX	INTEGER
			MAX-ACCESS	read-only
			STATUS	current
			::= { hmWanMbusB5 7 }

hmWanMbusB5VIF01		OBJECT-TYPE
			SYNTAX	INTEGER
			MAX-ACCESS	read-only
			STATUS	current
			::= { hmWanMbusB5 8 }

hmWanMbusB5Value01		OBJECT-TYPE
			SYNTAX	INTEGER
			MAX-ACCESS	read-only
			STATUS	current
			::= { hmWanMbusB5 9 }

hmWanMbusB5VIF02		OBJECT-TYPE
			SYNTAX	INTEGER
			MAX-ACCESS	read-only
			STATUS	current
			::= { hmWanMbusB5 10 }

hmWanMbusB5Value02		OBJECT-TYPE
			SYNTAX	INTEGER
			MAX-ACCESS	read-only
			STATUS	current
			::= { hmWanMbusB5 11 }

hmWanMbusB5VIF03		OBJECT-TYPE
			SYNTAX	INTEGER
			MAX-ACCESS	read-only
			STATUS	current
			::= { hmWanMbusB5 12 }

hmWanMbusB5Value03		OBJECT-TYPE
			SYNTAX	INTEGER
			MAX-ACCESS	read-only
			STATUS	current
			::= { hmWanMbusB5 13 }

hmWanMbusB5VIF04		OBJECT-TYPE
			SYNTAX	INTEGER
			MAX-ACCESS	read-only
			STATUS	current
			::= { hmWanMbusB5 14 }

hmWanMbusB5Value04		OBJECT-TYPE
			SYNTAX	INTEGER
			MAX-ACCESS	read-only
			STATUS	current
			::= { hmWanMbusB5 15 }

hmWanMbusB5VIF05		OBJECT-TYPE
			SYNTAX	INTEGER
			MAX-ACCESS	read-only
			STATUS	current
			::= { hmWanMbusB5 16 }

hmWanMbusB5Value05		OBJECT-TYPE
			SYNTAX	INTEGER
			MAX-ACCESS	read-only
			STATUS	current
			::= { hmWanMbusB5 17 }

hmWanMbusB5VIF06		OBJECT-TYPE
			SYNTAX	INTEGER
			MAX-ACCESS	read-only
			STATUS	current
			::= { hmWanMbusB5 18 }

hmWanMbusB5Value06		OBJECT-TYPE
			SYNTAX	INTEGER
			MAX-ACCESS	read-only
			STATUS	current
			::= { hmWanMbusB5 19 }

hmWanMbusB5VIF07		OBJECT-TYPE
			SYNTAX	INTEGER
			MAX-ACCESS	read-only
			STATUS	current
			::= { hmWanMbusB5 20 }

hmWanMbusB5Value07		OBJECT-TYPE
			SYNTAX	INTEGER
			MAX-ACCESS	read-only
			STATUS	current
			::= { hmWanMbusB5 21 }

hmWanMbusB5VIF08		OBJECT-TYPE
			SYNTAX	INTEGER
			MAX-ACCESS	read-only
			STATUS	current
			::= { hmWanMbusB5 22 }

hmWanMbusB5Value08		OBJECT-TYPE
			SYNTAX	INTEGER
			MAX-ACCESS	read-only
			STATUS	current
			::= { hmWanMbusB5 23 }

hmWanMbusB5VIF09		OBJECT-TYPE
			SYNTAX	INTEGER
			MAX-ACCESS	read-only
			STATUS	current
			::= { hmWanMbusB5 24 }

hmWanMbusB5Value09		OBJECT-TYPE
			SYNTAX	INTEGER
			MAX-ACCESS	read-only
			STATUS	current
			::= { hmWanMbusB5 25 }

hmWanMbusB5VIF0A		OBJECT-TYPE
			SYNTAX	INTEGER
			MAX-ACCESS	read-only
			STATUS	current
			::= { hmWanMbusB5 26 }

hmWanMbusB5Value0A		OBJECT-TYPE
			SYNTAX	INTEGER
			MAX-ACCESS	read-only
			STATUS	current
			::= { hmWanMbusB5 27 }

hmWanMbusB5VIF0B		OBJECT-TYPE
			SYNTAX	INTEGER
			MAX-ACCESS	read-only
			STATUS	current
			::= { hmWanMbusB5 28 }

hmWanMbusB5Value0B		OBJECT-TYPE
			SYNTAX	INTEGER
			MAX-ACCESS	read-only
			STATUS	current
			::= { hmWanMbusB5 29 }

hmWanMbusB5VIF0C		OBJECT-TYPE
			SYNTAX	INTEGER
			MAX-ACCESS	read-only
			STATUS	current
			::= { hmWanMbusB5 30 }

hmWanMbusB5Value0C		OBJECT-TYPE
			SYNTAX	INTEGER
			MAX-ACCESS	read-only
			STATUS	current
			::= { hmWanMbusB5 31 }

hmWanMbusB5VIF0D		OBJECT-TYPE
			SYNTAX	INTEGER
			MAX-ACCESS	read-only
			STATUS	current
			::= { hmWanMbusB5 32 }

hmWanMbusB5Value0D		OBJECT-TYPE
			SYNTAX	INTEGER
			MAX-ACCESS	read-only
			STATUS	current
			::= { hmWanMbusB5 33 }

hmWanMbusB5VIF0E		OBJECT-TYPE
			SYNTAX	INTEGER
			MAX-ACCESS	read-only
			STATUS	current
			::= { hmWanMbusB5 34 }

hmWanMbusB5Value0E		OBJECT-TYPE
			SYNTAX	INTEGER
			MAX-ACCESS	read-only
			STATUS	current
			::= { hmWanMbusB5 35 }

hmWanMbusB5VIF0F		OBJECT-TYPE
			SYNTAX	INTEGER
			MAX-ACCESS	read-only
			STATUS	current
			::= { hmWanMbusB5 36 }

hmWanMbusB5Value0F		OBJECT-TYPE
			SYNTAX	INTEGER
			MAX-ACCESS	read-only
			STATUS	current
			::= { hmWanMbusB5 37 }

hmWanMbusB5VIF10		OBJECT-TYPE
			SYNTAX	INTEGER
			MAX-ACCESS	read-only
			STATUS	current
			::= { hmWanMbusB5 38 }

hmWanMbusB5Value10		OBJECT-TYPE
			SYNTAX	INTEGER
			MAX-ACCESS	read-only
			STATUS	current
			::= { hmWanMbusB5 39 }

hmWanMbusB5VIF11		OBJECT-TYPE
			SYNTAX	INTEGER
			MAX-ACCESS	read-only
			STATUS	current
			::= { hmWanMbusB5 40 }

hmWanMbusB5Value11		OBJECT-TYPE
			SYNTAX	INTEGER
			MAX-ACCESS	read-only
			STATUS	current
			::= { hmWanMbusB5 41 }

hmWanMbusB5VIF12		OBJECT-TYPE
			SYNTAX	INTEGER
			MAX-ACCESS	read-only
			STATUS	current
			::= { hmWanMbusB5 42 }

hmWanMbusB5Value12		OBJECT-TYPE
			SYNTAX	INTEGER
			MAX-ACCESS	read-only
			STATUS	current
			::= { hmWanMbusB5 43 }

hmWanMbusB5VIF13		OBJECT-TYPE
			SYNTAX	INTEGER
			MAX-ACCESS	read-only
			STATUS	current
			::= { hmWanMbusB5 44 }

hmWanMbusB5Value13		OBJECT-TYPE
			SYNTAX	INTEGER
			MAX-ACCESS	read-only
			STATUS	current
			::= { hmWanMbusB5 45 }

hmWanMbusB5VIF14		OBJECT-TYPE
			SYNTAX	INTEGER
			MAX-ACCESS	read-only
			STATUS	current
			::= { hmWanMbusB5 46 }

hmWanMbusB5Value14		OBJECT-TYPE
			SYNTAX	INTEGER
			MAX-ACCESS	read-only
			STATUS	current
			::= { hmWanMbusB5 47 }

hmWanMbusB5VIF15		OBJECT-TYPE
			SYNTAX	INTEGER
			MAX-ACCESS	read-only
			STATUS	current
			::= { hmWanMbusB5 48 }

hmWanMbusB5Value15		OBJECT-TYPE
			SYNTAX	INTEGER
			MAX-ACCESS	read-only
			STATUS	current
			::= { hmWanMbusB5 49 }

hmWanMbusB5VIF16		OBJECT-TYPE
			SYNTAX	INTEGER
			MAX-ACCESS	read-only
			STATUS	current
			::= { hmWanMbusB5 50 }

hmWanMbusB5Value16		OBJECT-TYPE
			SYNTAX	INTEGER
			MAX-ACCESS	read-only
			STATUS	current
			::= { hmWanMbusB5 51 }

hmWanMbusB5VIF17		OBJECT-TYPE
			SYNTAX	INTEGER
			MAX-ACCESS	read-only
			STATUS	current
			::= { hmWanMbusB5 52 }

hmWanMbusB5Value17		OBJECT-TYPE
			SYNTAX	INTEGER
			MAX-ACCESS	read-only
			STATUS	current
			::= { hmWanMbusB5 53 }

hmWanMbusB5VIF18		OBJECT-TYPE
			SYNTAX	INTEGER
			MAX-ACCESS	read-only
			STATUS	current
			::= { hmWanMbusB5 54 }

hmWanMbusB5Value18		OBJECT-TYPE
			SYNTAX	INTEGER
			MAX-ACCESS	read-only
			STATUS	current
			::= { hmWanMbusB5 55 }

hmWanMbusB5VIF19		OBJECT-TYPE
			SYNTAX	INTEGER
			MAX-ACCESS	read-only
			STATUS	current
			::= { hmWanMbusB5 56 }

hmWanMbusB5Value19		OBJECT-TYPE
			SYNTAX	INTEGER
			MAX-ACCESS	read-only
			STATUS	current
			::= { hmWanMbusB5 57 }

hmWanMbusB5VIF1A		OBJECT-TYPE
			SYNTAX	INTEGER
			MAX-ACCESS	read-only
			STATUS	current
			::= { hmWanMbusB5 58 }

hmWanMbusB5Value1A		OBJECT-TYPE
			SYNTAX	INTEGER
			MAX-ACCESS	read-only
			STATUS	current
			::= { hmWanMbusB5 59 }

hmWanMbusB5VIF1B		OBJECT-TYPE
			SYNTAX	INTEGER
			MAX-ACCESS	read-only
			STATUS	current
			::= { hmWanMbusB5 60 }

hmWanMbusB5Value1B		OBJECT-TYPE
			SYNTAX	INTEGER
			MAX-ACCESS	read-only
			STATUS	current
			::= { hmWanMbusB5 61 }

hmWanMbusB5VIF1C		OBJECT-TYPE
			SYNTAX	INTEGER
			MAX-ACCESS	read-only
			STATUS	current
			::= { hmWanMbusB5 62 }

hmWanMbusB5Value1C		OBJECT-TYPE
			SYNTAX	INTEGER
			MAX-ACCESS	read-only
			STATUS	current
			::= { hmWanMbusB5 63 }

hmWanMbusB5VIF1D		OBJECT-TYPE
			SYNTAX	INTEGER
			MAX-ACCESS	read-only
			STATUS	current
			::= { hmWanMbusB5 64 }

hmWanMbusB5Value1D		OBJECT-TYPE
			SYNTAX	INTEGER
			MAX-ACCESS	read-only
			STATUS	current
			::= { hmWanMbusB5 65 }

hmWanMbusB5VIF1E		OBJECT-TYPE
			SYNTAX	INTEGER
			MAX-ACCESS	read-only
			STATUS	current
			::= { hmWanMbusB5 66 }

hmWanMbusB5Value1E		OBJECT-TYPE
			SYNTAX	INTEGER
			MAX-ACCESS	read-only
			STATUS	current
			::= { hmWanMbusB5 67 }

hmWanMbusB5VIF1F		OBJECT-TYPE
			SYNTAX	INTEGER
			MAX-ACCESS	read-only
			STATUS	current
			::= { hmWanMbusB5 68 }

hmWanMbusB5Value1F		OBJECT-TYPE
			SYNTAX	INTEGER
			MAX-ACCESS	read-only
			STATUS	current
			::= { hmWanMbusB5 69 }

hmWanMbusB5VIF20		OBJECT-TYPE
			SYNTAX	INTEGER
			MAX-ACCESS	read-only
			STATUS	current
			::= { hmWanMbusB5 70 }

hmWanMbusB5Value20		OBJECT-TYPE
			SYNTAX	INTEGER
			MAX-ACCESS	read-only
			STATUS	current
			::= { hmWanMbusB5 71 }

hmWanMbusB5VIF21		OBJECT-TYPE
			SYNTAX	INTEGER
			MAX-ACCESS	read-only
			STATUS	current
			::= { hmWanMbusB5 72 }

hmWanMbusB5Value21		OBJECT-TYPE
			SYNTAX	INTEGER
			MAX-ACCESS	read-only
			STATUS	current
			::= { hmWanMbusB5 73 }

hmWanMbusB5VIF22		OBJECT-TYPE
			SYNTAX	INTEGER
			MAX-ACCESS	read-only
			STATUS	current
			::= { hmWanMbusB5 74 }

hmWanMbusB5Value22		OBJECT-TYPE
			SYNTAX	INTEGER
			MAX-ACCESS	read-only
			STATUS	current
			::= { hmWanMbusB5 75 }

hmWanMbusB5VIF23		OBJECT-TYPE
			SYNTAX	INTEGER
			MAX-ACCESS	read-only
			STATUS	current
			::= { hmWanMbusB5 76 }

hmWanMbusB5Value23		OBJECT-TYPE
			SYNTAX	INTEGER
			MAX-ACCESS	read-only
			STATUS	current
			::= { hmWanMbusB5 77 }

hmWanMbusB5VIF24		OBJECT-TYPE
			SYNTAX	INTEGER
			MAX-ACCESS	read-only
			STATUS	current
			::= { hmWanMbusB5 78 }

hmWanMbusB5Value24		OBJECT-TYPE
			SYNTAX	INTEGER
			MAX-ACCESS	read-only
			STATUS	current
			::= { hmWanMbusB5 79 }

hmWanMbusB5VIF25		OBJECT-TYPE
			SYNTAX	INTEGER
			MAX-ACCESS	read-only
			STATUS	current
			::= { hmWanMbusB5 80 }

hmWanMbusB5Value25		OBJECT-TYPE
			SYNTAX	INTEGER
			MAX-ACCESS	read-only
			STATUS	current
			::= { hmWanMbusB5 81 }

hmWanMbusB5VIF26		OBJECT-TYPE
			SYNTAX	INTEGER
			MAX-ACCESS	read-only
			STATUS	current
			::= { hmWanMbusB5 82 }

hmWanMbusB5Value26		OBJECT-TYPE
			SYNTAX	INTEGER
			MAX-ACCESS	read-only
			STATUS	current
			::= { hmWanMbusB5 83 }

hmWanMbusB5VIF27		OBJECT-TYPE
			SYNTAX	INTEGER
			MAX-ACCESS	read-only
			STATUS	current
			::= { hmWanMbusB5 84 }

hmWanMbusB5Value27		OBJECT-TYPE
			SYNTAX	INTEGER
			MAX-ACCESS	read-only
			STATUS	current
			::= { hmWanMbusB5 85 }

hmWanMbusB5VIF28		OBJECT-TYPE
			SYNTAX	INTEGER
			MAX-ACCESS	read-only
			STATUS	current
			::= { hmWanMbusB5 86 }

hmWanMbusB5Value28		OBJECT-TYPE
			SYNTAX	INTEGER
			MAX-ACCESS	read-only
			STATUS	current
			::= { hmWanMbusB5 87 }

hmWanMbusB5VIF29		OBJECT-TYPE
			SYNTAX	INTEGER
			MAX-ACCESS	read-only
			STATUS	current
			::= { hmWanMbusB5 88 }

hmWanMbusB5Value29		OBJECT-TYPE
			SYNTAX	INTEGER
			MAX-ACCESS	read-only
			STATUS	current
			::= { hmWanMbusB5 89 }

hmWanMbusB5VIF2A		OBJECT-TYPE
			SYNTAX	INTEGER
			MAX-ACCESS	read-only
			STATUS	current
			::= { hmWanMbusB5 90 }

hmWanMbusB5Value2A		OBJECT-TYPE
			SYNTAX	INTEGER
			MAX-ACCESS	read-only
			STATUS	current
			::= { hmWanMbusB5 91 }

hmWanMbusB5VIF2B		OBJECT-TYPE
			SYNTAX	INTEGER
			MAX-ACCESS	read-only
			STATUS	current
			::= { hmWanMbusB5 92 }

hmWanMbusB5Value2B		OBJECT-TYPE
			SYNTAX	INTEGER
			MAX-ACCESS	read-only
			STATUS	current
			::= { hmWanMbusB5 93 }

hmWanMbusB5VIF2C		OBJECT-TYPE
			SYNTAX	INTEGER
			MAX-ACCESS	read-only
			STATUS	current
			::= { hmWanMbusB5 94 }

hmWanMbusB5Value2C		OBJECT-TYPE
			SYNTAX	INTEGER
			MAX-ACCESS	read-only
			STATUS	current
			::= { hmWanMbusB5 95 }

hmWanMbusB5VIF2D		OBJECT-TYPE
			SYNTAX	INTEGER
			MAX-ACCESS	read-only
			STATUS	current
			::= { hmWanMbusB5 96 }

hmWanMbusB5Value2D		OBJECT-TYPE
			SYNTAX	INTEGER
			MAX-ACCESS	read-only
			STATUS	current
			::= { hmWanMbusB5 97 }

hmWanMbusB5VIF2E		OBJECT-TYPE
			SYNTAX	INTEGER
			MAX-ACCESS	read-only
			STATUS	current
			::= { hmWanMbusB5 98 }

hmWanMbusB5Value2E		OBJECT-TYPE
			SYNTAX	INTEGER
			MAX-ACCESS	read-only
			STATUS	current
			::= { hmWanMbusB5 99 }

hmWanMbusB5VIF2F		OBJECT-TYPE
			SYNTAX	INTEGER
			MAX-ACCESS	read-only
			STATUS	current
			::= { hmWanMbusB5 100 }

hmWanMbusB5Value2F		OBJECT-TYPE
			SYNTAX	INTEGER
			MAX-ACCESS	read-only
			STATUS	current
			::= { hmWanMbusB5 101 }

hmWanMbusB6			OBJECT IDENTIFIER ::= { hmWanMbus 182 }

hmWanMbusB6IdNumber		OBJECT-TYPE
			SYNTAX	Gauge32
			MAX-ACCESS	read-only
			STATUS	current
			::= { hmWanMbusB6 1 }

hmWanMbusB6Manufacturer	OBJECT-TYPE
			SYNTAX	Gauge32
			MAX-ACCESS	read-only
			STATUS	current
			::= { hmWanMbusB6 2 }

hmWanMbusB6Version		OBJECT-TYPE
			SYNTAX	Gauge32
			MAX-ACCESS	read-only
			STATUS	current
			::= { hmWanMbusB6 3 }

hmWanMbusB6Medium		OBJECT-TYPE
			SYNTAX	Gauge32
			MAX-ACCESS	read-only
			STATUS	current
			::= { hmWanMbusB6 4 }

hmWanMbusB6Status		OBJECT-TYPE
			SYNTAX	Gauge32
			MAX-ACCESS	read-only
			STATUS	current
			::= { hmWanMbusB6 5 }

hmWanMbusB6VIF00		OBJECT-TYPE
			SYNTAX	INTEGER
			MAX-ACCESS	read-only
			STATUS	current
			::= { hmWanMbusB6 6 }

hmWanMbusB6Value00		OBJECT-TYPE
			SYNTAX	INTEGER
			MAX-ACCESS	read-only
			STATUS	current
			::= { hmWanMbusB6 7 }

hmWanMbusB6VIF01		OBJECT-TYPE
			SYNTAX	INTEGER
			MAX-ACCESS	read-only
			STATUS	current
			::= { hmWanMbusB6 8 }

hmWanMbusB6Value01		OBJECT-TYPE
			SYNTAX	INTEGER
			MAX-ACCESS	read-only
			STATUS	current
			::= { hmWanMbusB6 9 }

hmWanMbusB6VIF02		OBJECT-TYPE
			SYNTAX	INTEGER
			MAX-ACCESS	read-only
			STATUS	current
			::= { hmWanMbusB6 10 }

hmWanMbusB6Value02		OBJECT-TYPE
			SYNTAX	INTEGER
			MAX-ACCESS	read-only
			STATUS	current
			::= { hmWanMbusB6 11 }

hmWanMbusB6VIF03		OBJECT-TYPE
			SYNTAX	INTEGER
			MAX-ACCESS	read-only
			STATUS	current
			::= { hmWanMbusB6 12 }

hmWanMbusB6Value03		OBJECT-TYPE
			SYNTAX	INTEGER
			MAX-ACCESS	read-only
			STATUS	current
			::= { hmWanMbusB6 13 }

hmWanMbusB6VIF04		OBJECT-TYPE
			SYNTAX	INTEGER
			MAX-ACCESS	read-only
			STATUS	current
			::= { hmWanMbusB6 14 }

hmWanMbusB6Value04		OBJECT-TYPE
			SYNTAX	INTEGER
			MAX-ACCESS	read-only
			STATUS	current
			::= { hmWanMbusB6 15 }

hmWanMbusB6VIF05		OBJECT-TYPE
			SYNTAX	INTEGER
			MAX-ACCESS	read-only
			STATUS	current
			::= { hmWanMbusB6 16 }

hmWanMbusB6Value05		OBJECT-TYPE
			SYNTAX	INTEGER
			MAX-ACCESS	read-only
			STATUS	current
			::= { hmWanMbusB6 17 }

hmWanMbusB6VIF06		OBJECT-TYPE
			SYNTAX	INTEGER
			MAX-ACCESS	read-only
			STATUS	current
			::= { hmWanMbusB6 18 }

hmWanMbusB6Value06		OBJECT-TYPE
			SYNTAX	INTEGER
			MAX-ACCESS	read-only
			STATUS	current
			::= { hmWanMbusB6 19 }

hmWanMbusB6VIF07		OBJECT-TYPE
			SYNTAX	INTEGER
			MAX-ACCESS	read-only
			STATUS	current
			::= { hmWanMbusB6 20 }

hmWanMbusB6Value07		OBJECT-TYPE
			SYNTAX	INTEGER
			MAX-ACCESS	read-only
			STATUS	current
			::= { hmWanMbusB6 21 }

hmWanMbusB6VIF08		OBJECT-TYPE
			SYNTAX	INTEGER
			MAX-ACCESS	read-only
			STATUS	current
			::= { hmWanMbusB6 22 }

hmWanMbusB6Value08		OBJECT-TYPE
			SYNTAX	INTEGER
			MAX-ACCESS	read-only
			STATUS	current
			::= { hmWanMbusB6 23 }

hmWanMbusB6VIF09		OBJECT-TYPE
			SYNTAX	INTEGER
			MAX-ACCESS	read-only
			STATUS	current
			::= { hmWanMbusB6 24 }

hmWanMbusB6Value09		OBJECT-TYPE
			SYNTAX	INTEGER
			MAX-ACCESS	read-only
			STATUS	current
			::= { hmWanMbusB6 25 }

hmWanMbusB6VIF0A		OBJECT-TYPE
			SYNTAX	INTEGER
			MAX-ACCESS	read-only
			STATUS	current
			::= { hmWanMbusB6 26 }

hmWanMbusB6Value0A		OBJECT-TYPE
			SYNTAX	INTEGER
			MAX-ACCESS	read-only
			STATUS	current
			::= { hmWanMbusB6 27 }

hmWanMbusB6VIF0B		OBJECT-TYPE
			SYNTAX	INTEGER
			MAX-ACCESS	read-only
			STATUS	current
			::= { hmWanMbusB6 28 }

hmWanMbusB6Value0B		OBJECT-TYPE
			SYNTAX	INTEGER
			MAX-ACCESS	read-only
			STATUS	current
			::= { hmWanMbusB6 29 }

hmWanMbusB6VIF0C		OBJECT-TYPE
			SYNTAX	INTEGER
			MAX-ACCESS	read-only
			STATUS	current
			::= { hmWanMbusB6 30 }

hmWanMbusB6Value0C		OBJECT-TYPE
			SYNTAX	INTEGER
			MAX-ACCESS	read-only
			STATUS	current
			::= { hmWanMbusB6 31 }

hmWanMbusB6VIF0D		OBJECT-TYPE
			SYNTAX	INTEGER
			MAX-ACCESS	read-only
			STATUS	current
			::= { hmWanMbusB6 32 }

hmWanMbusB6Value0D		OBJECT-TYPE
			SYNTAX	INTEGER
			MAX-ACCESS	read-only
			STATUS	current
			::= { hmWanMbusB6 33 }

hmWanMbusB6VIF0E		OBJECT-TYPE
			SYNTAX	INTEGER
			MAX-ACCESS	read-only
			STATUS	current
			::= { hmWanMbusB6 34 }

hmWanMbusB6Value0E		OBJECT-TYPE
			SYNTAX	INTEGER
			MAX-ACCESS	read-only
			STATUS	current
			::= { hmWanMbusB6 35 }

hmWanMbusB6VIF0F		OBJECT-TYPE
			SYNTAX	INTEGER
			MAX-ACCESS	read-only
			STATUS	current
			::= { hmWanMbusB6 36 }

hmWanMbusB6Value0F		OBJECT-TYPE
			SYNTAX	INTEGER
			MAX-ACCESS	read-only
			STATUS	current
			::= { hmWanMbusB6 37 }

hmWanMbusB6VIF10		OBJECT-TYPE
			SYNTAX	INTEGER
			MAX-ACCESS	read-only
			STATUS	current
			::= { hmWanMbusB6 38 }

hmWanMbusB6Value10		OBJECT-TYPE
			SYNTAX	INTEGER
			MAX-ACCESS	read-only
			STATUS	current
			::= { hmWanMbusB6 39 }

hmWanMbusB6VIF11		OBJECT-TYPE
			SYNTAX	INTEGER
			MAX-ACCESS	read-only
			STATUS	current
			::= { hmWanMbusB6 40 }

hmWanMbusB6Value11		OBJECT-TYPE
			SYNTAX	INTEGER
			MAX-ACCESS	read-only
			STATUS	current
			::= { hmWanMbusB6 41 }

hmWanMbusB6VIF12		OBJECT-TYPE
			SYNTAX	INTEGER
			MAX-ACCESS	read-only
			STATUS	current
			::= { hmWanMbusB6 42 }

hmWanMbusB6Value12		OBJECT-TYPE
			SYNTAX	INTEGER
			MAX-ACCESS	read-only
			STATUS	current
			::= { hmWanMbusB6 43 }

hmWanMbusB6VIF13		OBJECT-TYPE
			SYNTAX	INTEGER
			MAX-ACCESS	read-only
			STATUS	current
			::= { hmWanMbusB6 44 }

hmWanMbusB6Value13		OBJECT-TYPE
			SYNTAX	INTEGER
			MAX-ACCESS	read-only
			STATUS	current
			::= { hmWanMbusB6 45 }

hmWanMbusB6VIF14		OBJECT-TYPE
			SYNTAX	INTEGER
			MAX-ACCESS	read-only
			STATUS	current
			::= { hmWanMbusB6 46 }

hmWanMbusB6Value14		OBJECT-TYPE
			SYNTAX	INTEGER
			MAX-ACCESS	read-only
			STATUS	current
			::= { hmWanMbusB6 47 }

hmWanMbusB6VIF15		OBJECT-TYPE
			SYNTAX	INTEGER
			MAX-ACCESS	read-only
			STATUS	current
			::= { hmWanMbusB6 48 }

hmWanMbusB6Value15		OBJECT-TYPE
			SYNTAX	INTEGER
			MAX-ACCESS	read-only
			STATUS	current
			::= { hmWanMbusB6 49 }

hmWanMbusB6VIF16		OBJECT-TYPE
			SYNTAX	INTEGER
			MAX-ACCESS	read-only
			STATUS	current
			::= { hmWanMbusB6 50 }

hmWanMbusB6Value16		OBJECT-TYPE
			SYNTAX	INTEGER
			MAX-ACCESS	read-only
			STATUS	current
			::= { hmWanMbusB6 51 }

hmWanMbusB6VIF17		OBJECT-TYPE
			SYNTAX	INTEGER
			MAX-ACCESS	read-only
			STATUS	current
			::= { hmWanMbusB6 52 }

hmWanMbusB6Value17		OBJECT-TYPE
			SYNTAX	INTEGER
			MAX-ACCESS	read-only
			STATUS	current
			::= { hmWanMbusB6 53 }

hmWanMbusB6VIF18		OBJECT-TYPE
			SYNTAX	INTEGER
			MAX-ACCESS	read-only
			STATUS	current
			::= { hmWanMbusB6 54 }

hmWanMbusB6Value18		OBJECT-TYPE
			SYNTAX	INTEGER
			MAX-ACCESS	read-only
			STATUS	current
			::= { hmWanMbusB6 55 }

hmWanMbusB6VIF19		OBJECT-TYPE
			SYNTAX	INTEGER
			MAX-ACCESS	read-only
			STATUS	current
			::= { hmWanMbusB6 56 }

hmWanMbusB6Value19		OBJECT-TYPE
			SYNTAX	INTEGER
			MAX-ACCESS	read-only
			STATUS	current
			::= { hmWanMbusB6 57 }

hmWanMbusB6VIF1A		OBJECT-TYPE
			SYNTAX	INTEGER
			MAX-ACCESS	read-only
			STATUS	current
			::= { hmWanMbusB6 58 }

hmWanMbusB6Value1A		OBJECT-TYPE
			SYNTAX	INTEGER
			MAX-ACCESS	read-only
			STATUS	current
			::= { hmWanMbusB6 59 }

hmWanMbusB6VIF1B		OBJECT-TYPE
			SYNTAX	INTEGER
			MAX-ACCESS	read-only
			STATUS	current
			::= { hmWanMbusB6 60 }

hmWanMbusB6Value1B		OBJECT-TYPE
			SYNTAX	INTEGER
			MAX-ACCESS	read-only
			STATUS	current
			::= { hmWanMbusB6 61 }

hmWanMbusB6VIF1C		OBJECT-TYPE
			SYNTAX	INTEGER
			MAX-ACCESS	read-only
			STATUS	current
			::= { hmWanMbusB6 62 }

hmWanMbusB6Value1C		OBJECT-TYPE
			SYNTAX	INTEGER
			MAX-ACCESS	read-only
			STATUS	current
			::= { hmWanMbusB6 63 }

hmWanMbusB6VIF1D		OBJECT-TYPE
			SYNTAX	INTEGER
			MAX-ACCESS	read-only
			STATUS	current
			::= { hmWanMbusB6 64 }

hmWanMbusB6Value1D		OBJECT-TYPE
			SYNTAX	INTEGER
			MAX-ACCESS	read-only
			STATUS	current
			::= { hmWanMbusB6 65 }

hmWanMbusB6VIF1E		OBJECT-TYPE
			SYNTAX	INTEGER
			MAX-ACCESS	read-only
			STATUS	current
			::= { hmWanMbusB6 66 }

hmWanMbusB6Value1E		OBJECT-TYPE
			SYNTAX	INTEGER
			MAX-ACCESS	read-only
			STATUS	current
			::= { hmWanMbusB6 67 }

hmWanMbusB6VIF1F		OBJECT-TYPE
			SYNTAX	INTEGER
			MAX-ACCESS	read-only
			STATUS	current
			::= { hmWanMbusB6 68 }

hmWanMbusB6Value1F		OBJECT-TYPE
			SYNTAX	INTEGER
			MAX-ACCESS	read-only
			STATUS	current
			::= { hmWanMbusB6 69 }

hmWanMbusB6VIF20		OBJECT-TYPE
			SYNTAX	INTEGER
			MAX-ACCESS	read-only
			STATUS	current
			::= { hmWanMbusB6 70 }

hmWanMbusB6Value20		OBJECT-TYPE
			SYNTAX	INTEGER
			MAX-ACCESS	read-only
			STATUS	current
			::= { hmWanMbusB6 71 }

hmWanMbusB6VIF21		OBJECT-TYPE
			SYNTAX	INTEGER
			MAX-ACCESS	read-only
			STATUS	current
			::= { hmWanMbusB6 72 }

hmWanMbusB6Value21		OBJECT-TYPE
			SYNTAX	INTEGER
			MAX-ACCESS	read-only
			STATUS	current
			::= { hmWanMbusB6 73 }

hmWanMbusB6VIF22		OBJECT-TYPE
			SYNTAX	INTEGER
			MAX-ACCESS	read-only
			STATUS	current
			::= { hmWanMbusB6 74 }

hmWanMbusB6Value22		OBJECT-TYPE
			SYNTAX	INTEGER
			MAX-ACCESS	read-only
			STATUS	current
			::= { hmWanMbusB6 75 }

hmWanMbusB6VIF23		OBJECT-TYPE
			SYNTAX	INTEGER
			MAX-ACCESS	read-only
			STATUS	current
			::= { hmWanMbusB6 76 }

hmWanMbusB6Value23		OBJECT-TYPE
			SYNTAX	INTEGER
			MAX-ACCESS	read-only
			STATUS	current
			::= { hmWanMbusB6 77 }

hmWanMbusB6VIF24		OBJECT-TYPE
			SYNTAX	INTEGER
			MAX-ACCESS	read-only
			STATUS	current
			::= { hmWanMbusB6 78 }

hmWanMbusB6Value24		OBJECT-TYPE
			SYNTAX	INTEGER
			MAX-ACCESS	read-only
			STATUS	current
			::= { hmWanMbusB6 79 }

hmWanMbusB6VIF25		OBJECT-TYPE
			SYNTAX	INTEGER
			MAX-ACCESS	read-only
			STATUS	current
			::= { hmWanMbusB6 80 }

hmWanMbusB6Value25		OBJECT-TYPE
			SYNTAX	INTEGER
			MAX-ACCESS	read-only
			STATUS	current
			::= { hmWanMbusB6 81 }

hmWanMbusB6VIF26		OBJECT-TYPE
			SYNTAX	INTEGER
			MAX-ACCESS	read-only
			STATUS	current
			::= { hmWanMbusB6 82 }

hmWanMbusB6Value26		OBJECT-TYPE
			SYNTAX	INTEGER
			MAX-ACCESS	read-only
			STATUS	current
			::= { hmWanMbusB6 83 }

hmWanMbusB6VIF27		OBJECT-TYPE
			SYNTAX	INTEGER
			MAX-ACCESS	read-only
			STATUS	current
			::= { hmWanMbusB6 84 }

hmWanMbusB6Value27		OBJECT-TYPE
			SYNTAX	INTEGER
			MAX-ACCESS	read-only
			STATUS	current
			::= { hmWanMbusB6 85 }

hmWanMbusB6VIF28		OBJECT-TYPE
			SYNTAX	INTEGER
			MAX-ACCESS	read-only
			STATUS	current
			::= { hmWanMbusB6 86 }

hmWanMbusB6Value28		OBJECT-TYPE
			SYNTAX	INTEGER
			MAX-ACCESS	read-only
			STATUS	current
			::= { hmWanMbusB6 87 }

hmWanMbusB6VIF29		OBJECT-TYPE
			SYNTAX	INTEGER
			MAX-ACCESS	read-only
			STATUS	current
			::= { hmWanMbusB6 88 }

hmWanMbusB6Value29		OBJECT-TYPE
			SYNTAX	INTEGER
			MAX-ACCESS	read-only
			STATUS	current
			::= { hmWanMbusB6 89 }

hmWanMbusB6VIF2A		OBJECT-TYPE
			SYNTAX	INTEGER
			MAX-ACCESS	read-only
			STATUS	current
			::= { hmWanMbusB6 90 }

hmWanMbusB6Value2A		OBJECT-TYPE
			SYNTAX	INTEGER
			MAX-ACCESS	read-only
			STATUS	current
			::= { hmWanMbusB6 91 }

hmWanMbusB6VIF2B		OBJECT-TYPE
			SYNTAX	INTEGER
			MAX-ACCESS	read-only
			STATUS	current
			::= { hmWanMbusB6 92 }

hmWanMbusB6Value2B		OBJECT-TYPE
			SYNTAX	INTEGER
			MAX-ACCESS	read-only
			STATUS	current
			::= { hmWanMbusB6 93 }

hmWanMbusB6VIF2C		OBJECT-TYPE
			SYNTAX	INTEGER
			MAX-ACCESS	read-only
			STATUS	current
			::= { hmWanMbusB6 94 }

hmWanMbusB6Value2C		OBJECT-TYPE
			SYNTAX	INTEGER
			MAX-ACCESS	read-only
			STATUS	current
			::= { hmWanMbusB6 95 }

hmWanMbusB6VIF2D		OBJECT-TYPE
			SYNTAX	INTEGER
			MAX-ACCESS	read-only
			STATUS	current
			::= { hmWanMbusB6 96 }

hmWanMbusB6Value2D		OBJECT-TYPE
			SYNTAX	INTEGER
			MAX-ACCESS	read-only
			STATUS	current
			::= { hmWanMbusB6 97 }

hmWanMbusB6VIF2E		OBJECT-TYPE
			SYNTAX	INTEGER
			MAX-ACCESS	read-only
			STATUS	current
			::= { hmWanMbusB6 98 }

hmWanMbusB6Value2E		OBJECT-TYPE
			SYNTAX	INTEGER
			MAX-ACCESS	read-only
			STATUS	current
			::= { hmWanMbusB6 99 }

hmWanMbusB6VIF2F		OBJECT-TYPE
			SYNTAX	INTEGER
			MAX-ACCESS	read-only
			STATUS	current
			::= { hmWanMbusB6 100 }

hmWanMbusB6Value2F		OBJECT-TYPE
			SYNTAX	INTEGER
			MAX-ACCESS	read-only
			STATUS	current
			::= { hmWanMbusB6 101 }

hmWanMbusB7			OBJECT IDENTIFIER ::= { hmWanMbus 183 }

hmWanMbusB7IdNumber		OBJECT-TYPE
			SYNTAX	Gauge32
			MAX-ACCESS	read-only
			STATUS	current
			::= { hmWanMbusB7 1 }

hmWanMbusB7Manufacturer	OBJECT-TYPE
			SYNTAX	Gauge32
			MAX-ACCESS	read-only
			STATUS	current
			::= { hmWanMbusB7 2 }

hmWanMbusB7Version		OBJECT-TYPE
			SYNTAX	Gauge32
			MAX-ACCESS	read-only
			STATUS	current
			::= { hmWanMbusB7 3 }

hmWanMbusB7Medium		OBJECT-TYPE
			SYNTAX	Gauge32
			MAX-ACCESS	read-only
			STATUS	current
			::= { hmWanMbusB7 4 }

hmWanMbusB7Status		OBJECT-TYPE
			SYNTAX	Gauge32
			MAX-ACCESS	read-only
			STATUS	current
			::= { hmWanMbusB7 5 }

hmWanMbusB7VIF00		OBJECT-TYPE
			SYNTAX	INTEGER
			MAX-ACCESS	read-only
			STATUS	current
			::= { hmWanMbusB7 6 }

hmWanMbusB7Value00		OBJECT-TYPE
			SYNTAX	INTEGER
			MAX-ACCESS	read-only
			STATUS	current
			::= { hmWanMbusB7 7 }

hmWanMbusB7VIF01		OBJECT-TYPE
			SYNTAX	INTEGER
			MAX-ACCESS	read-only
			STATUS	current
			::= { hmWanMbusB7 8 }

hmWanMbusB7Value01		OBJECT-TYPE
			SYNTAX	INTEGER
			MAX-ACCESS	read-only
			STATUS	current
			::= { hmWanMbusB7 9 }

hmWanMbusB7VIF02		OBJECT-TYPE
			SYNTAX	INTEGER
			MAX-ACCESS	read-only
			STATUS	current
			::= { hmWanMbusB7 10 }

hmWanMbusB7Value02		OBJECT-TYPE
			SYNTAX	INTEGER
			MAX-ACCESS	read-only
			STATUS	current
			::= { hmWanMbusB7 11 }

hmWanMbusB7VIF03		OBJECT-TYPE
			SYNTAX	INTEGER
			MAX-ACCESS	read-only
			STATUS	current
			::= { hmWanMbusB7 12 }

hmWanMbusB7Value03		OBJECT-TYPE
			SYNTAX	INTEGER
			MAX-ACCESS	read-only
			STATUS	current
			::= { hmWanMbusB7 13 }

hmWanMbusB7VIF04		OBJECT-TYPE
			SYNTAX	INTEGER
			MAX-ACCESS	read-only
			STATUS	current
			::= { hmWanMbusB7 14 }

hmWanMbusB7Value04		OBJECT-TYPE
			SYNTAX	INTEGER
			MAX-ACCESS	read-only
			STATUS	current
			::= { hmWanMbusB7 15 }

hmWanMbusB7VIF05		OBJECT-TYPE
			SYNTAX	INTEGER
			MAX-ACCESS	read-only
			STATUS	current
			::= { hmWanMbusB7 16 }

hmWanMbusB7Value05		OBJECT-TYPE
			SYNTAX	INTEGER
			MAX-ACCESS	read-only
			STATUS	current
			::= { hmWanMbusB7 17 }

hmWanMbusB7VIF06		OBJECT-TYPE
			SYNTAX	INTEGER
			MAX-ACCESS	read-only
			STATUS	current
			::= { hmWanMbusB7 18 }

hmWanMbusB7Value06		OBJECT-TYPE
			SYNTAX	INTEGER
			MAX-ACCESS	read-only
			STATUS	current
			::= { hmWanMbusB7 19 }

hmWanMbusB7VIF07		OBJECT-TYPE
			SYNTAX	INTEGER
			MAX-ACCESS	read-only
			STATUS	current
			::= { hmWanMbusB7 20 }

hmWanMbusB7Value07		OBJECT-TYPE
			SYNTAX	INTEGER
			MAX-ACCESS	read-only
			STATUS	current
			::= { hmWanMbusB7 21 }

hmWanMbusB7VIF08		OBJECT-TYPE
			SYNTAX	INTEGER
			MAX-ACCESS	read-only
			STATUS	current
			::= { hmWanMbusB7 22 }

hmWanMbusB7Value08		OBJECT-TYPE
			SYNTAX	INTEGER
			MAX-ACCESS	read-only
			STATUS	current
			::= { hmWanMbusB7 23 }

hmWanMbusB7VIF09		OBJECT-TYPE
			SYNTAX	INTEGER
			MAX-ACCESS	read-only
			STATUS	current
			::= { hmWanMbusB7 24 }

hmWanMbusB7Value09		OBJECT-TYPE
			SYNTAX	INTEGER
			MAX-ACCESS	read-only
			STATUS	current
			::= { hmWanMbusB7 25 }

hmWanMbusB7VIF0A		OBJECT-TYPE
			SYNTAX	INTEGER
			MAX-ACCESS	read-only
			STATUS	current
			::= { hmWanMbusB7 26 }

hmWanMbusB7Value0A		OBJECT-TYPE
			SYNTAX	INTEGER
			MAX-ACCESS	read-only
			STATUS	current
			::= { hmWanMbusB7 27 }

hmWanMbusB7VIF0B		OBJECT-TYPE
			SYNTAX	INTEGER
			MAX-ACCESS	read-only
			STATUS	current
			::= { hmWanMbusB7 28 }

hmWanMbusB7Value0B		OBJECT-TYPE
			SYNTAX	INTEGER
			MAX-ACCESS	read-only
			STATUS	current
			::= { hmWanMbusB7 29 }

hmWanMbusB7VIF0C		OBJECT-TYPE
			SYNTAX	INTEGER
			MAX-ACCESS	read-only
			STATUS	current
			::= { hmWanMbusB7 30 }

hmWanMbusB7Value0C		OBJECT-TYPE
			SYNTAX	INTEGER
			MAX-ACCESS	read-only
			STATUS	current
			::= { hmWanMbusB7 31 }

hmWanMbusB7VIF0D		OBJECT-TYPE
			SYNTAX	INTEGER
			MAX-ACCESS	read-only
			STATUS	current
			::= { hmWanMbusB7 32 }

hmWanMbusB7Value0D		OBJECT-TYPE
			SYNTAX	INTEGER
			MAX-ACCESS	read-only
			STATUS	current
			::= { hmWanMbusB7 33 }

hmWanMbusB7VIF0E		OBJECT-TYPE
			SYNTAX	INTEGER
			MAX-ACCESS	read-only
			STATUS	current
			::= { hmWanMbusB7 34 }

hmWanMbusB7Value0E		OBJECT-TYPE
			SYNTAX	INTEGER
			MAX-ACCESS	read-only
			STATUS	current
			::= { hmWanMbusB7 35 }

hmWanMbusB7VIF0F		OBJECT-TYPE
			SYNTAX	INTEGER
			MAX-ACCESS	read-only
			STATUS	current
			::= { hmWanMbusB7 36 }

hmWanMbusB7Value0F		OBJECT-TYPE
			SYNTAX	INTEGER
			MAX-ACCESS	read-only
			STATUS	current
			::= { hmWanMbusB7 37 }

hmWanMbusB7VIF10		OBJECT-TYPE
			SYNTAX	INTEGER
			MAX-ACCESS	read-only
			STATUS	current
			::= { hmWanMbusB7 38 }

hmWanMbusB7Value10		OBJECT-TYPE
			SYNTAX	INTEGER
			MAX-ACCESS	read-only
			STATUS	current
			::= { hmWanMbusB7 39 }

hmWanMbusB7VIF11		OBJECT-TYPE
			SYNTAX	INTEGER
			MAX-ACCESS	read-only
			STATUS	current
			::= { hmWanMbusB7 40 }

hmWanMbusB7Value11		OBJECT-TYPE
			SYNTAX	INTEGER
			MAX-ACCESS	read-only
			STATUS	current
			::= { hmWanMbusB7 41 }

hmWanMbusB7VIF12		OBJECT-TYPE
			SYNTAX	INTEGER
			MAX-ACCESS	read-only
			STATUS	current
			::= { hmWanMbusB7 42 }

hmWanMbusB7Value12		OBJECT-TYPE
			SYNTAX	INTEGER
			MAX-ACCESS	read-only
			STATUS	current
			::= { hmWanMbusB7 43 }

hmWanMbusB7VIF13		OBJECT-TYPE
			SYNTAX	INTEGER
			MAX-ACCESS	read-only
			STATUS	current
			::= { hmWanMbusB7 44 }

hmWanMbusB7Value13		OBJECT-TYPE
			SYNTAX	INTEGER
			MAX-ACCESS	read-only
			STATUS	current
			::= { hmWanMbusB7 45 }

hmWanMbusB7VIF14		OBJECT-TYPE
			SYNTAX	INTEGER
			MAX-ACCESS	read-only
			STATUS	current
			::= { hmWanMbusB7 46 }

hmWanMbusB7Value14		OBJECT-TYPE
			SYNTAX	INTEGER
			MAX-ACCESS	read-only
			STATUS	current
			::= { hmWanMbusB7 47 }

hmWanMbusB7VIF15		OBJECT-TYPE
			SYNTAX	INTEGER
			MAX-ACCESS	read-only
			STATUS	current
			::= { hmWanMbusB7 48 }

hmWanMbusB7Value15		OBJECT-TYPE
			SYNTAX	INTEGER
			MAX-ACCESS	read-only
			STATUS	current
			::= { hmWanMbusB7 49 }

hmWanMbusB7VIF16		OBJECT-TYPE
			SYNTAX	INTEGER
			MAX-ACCESS	read-only
			STATUS	current
			::= { hmWanMbusB7 50 }

hmWanMbusB7Value16		OBJECT-TYPE
			SYNTAX	INTEGER
			MAX-ACCESS	read-only
			STATUS	current
			::= { hmWanMbusB7 51 }

hmWanMbusB7VIF17		OBJECT-TYPE
			SYNTAX	INTEGER
			MAX-ACCESS	read-only
			STATUS	current
			::= { hmWanMbusB7 52 }

hmWanMbusB7Value17		OBJECT-TYPE
			SYNTAX	INTEGER
			MAX-ACCESS	read-only
			STATUS	current
			::= { hmWanMbusB7 53 }

hmWanMbusB7VIF18		OBJECT-TYPE
			SYNTAX	INTEGER
			MAX-ACCESS	read-only
			STATUS	current
			::= { hmWanMbusB7 54 }

hmWanMbusB7Value18		OBJECT-TYPE
			SYNTAX	INTEGER
			MAX-ACCESS	read-only
			STATUS	current
			::= { hmWanMbusB7 55 }

hmWanMbusB7VIF19		OBJECT-TYPE
			SYNTAX	INTEGER
			MAX-ACCESS	read-only
			STATUS	current
			::= { hmWanMbusB7 56 }

hmWanMbusB7Value19		OBJECT-TYPE
			SYNTAX	INTEGER
			MAX-ACCESS	read-only
			STATUS	current
			::= { hmWanMbusB7 57 }

hmWanMbusB7VIF1A		OBJECT-TYPE
			SYNTAX	INTEGER
			MAX-ACCESS	read-only
			STATUS	current
			::= { hmWanMbusB7 58 }

hmWanMbusB7Value1A		OBJECT-TYPE
			SYNTAX	INTEGER
			MAX-ACCESS	read-only
			STATUS	current
			::= { hmWanMbusB7 59 }

hmWanMbusB7VIF1B		OBJECT-TYPE
			SYNTAX	INTEGER
			MAX-ACCESS	read-only
			STATUS	current
			::= { hmWanMbusB7 60 }

hmWanMbusB7Value1B		OBJECT-TYPE
			SYNTAX	INTEGER
			MAX-ACCESS	read-only
			STATUS	current
			::= { hmWanMbusB7 61 }

hmWanMbusB7VIF1C		OBJECT-TYPE
			SYNTAX	INTEGER
			MAX-ACCESS	read-only
			STATUS	current
			::= { hmWanMbusB7 62 }

hmWanMbusB7Value1C		OBJECT-TYPE
			SYNTAX	INTEGER
			MAX-ACCESS	read-only
			STATUS	current
			::= { hmWanMbusB7 63 }

hmWanMbusB7VIF1D		OBJECT-TYPE
			SYNTAX	INTEGER
			MAX-ACCESS	read-only
			STATUS	current
			::= { hmWanMbusB7 64 }

hmWanMbusB7Value1D		OBJECT-TYPE
			SYNTAX	INTEGER
			MAX-ACCESS	read-only
			STATUS	current
			::= { hmWanMbusB7 65 }

hmWanMbusB7VIF1E		OBJECT-TYPE
			SYNTAX	INTEGER
			MAX-ACCESS	read-only
			STATUS	current
			::= { hmWanMbusB7 66 }

hmWanMbusB7Value1E		OBJECT-TYPE
			SYNTAX	INTEGER
			MAX-ACCESS	read-only
			STATUS	current
			::= { hmWanMbusB7 67 }

hmWanMbusB7VIF1F		OBJECT-TYPE
			SYNTAX	INTEGER
			MAX-ACCESS	read-only
			STATUS	current
			::= { hmWanMbusB7 68 }

hmWanMbusB7Value1F		OBJECT-TYPE
			SYNTAX	INTEGER
			MAX-ACCESS	read-only
			STATUS	current
			::= { hmWanMbusB7 69 }

hmWanMbusB7VIF20		OBJECT-TYPE
			SYNTAX	INTEGER
			MAX-ACCESS	read-only
			STATUS	current
			::= { hmWanMbusB7 70 }

hmWanMbusB7Value20		OBJECT-TYPE
			SYNTAX	INTEGER
			MAX-ACCESS	read-only
			STATUS	current
			::= { hmWanMbusB7 71 }

hmWanMbusB7VIF21		OBJECT-TYPE
			SYNTAX	INTEGER
			MAX-ACCESS	read-only
			STATUS	current
			::= { hmWanMbusB7 72 }

hmWanMbusB7Value21		OBJECT-TYPE
			SYNTAX	INTEGER
			MAX-ACCESS	read-only
			STATUS	current
			::= { hmWanMbusB7 73 }

hmWanMbusB7VIF22		OBJECT-TYPE
			SYNTAX	INTEGER
			MAX-ACCESS	read-only
			STATUS	current
			::= { hmWanMbusB7 74 }

hmWanMbusB7Value22		OBJECT-TYPE
			SYNTAX	INTEGER
			MAX-ACCESS	read-only
			STATUS	current
			::= { hmWanMbusB7 75 }

hmWanMbusB7VIF23		OBJECT-TYPE
			SYNTAX	INTEGER
			MAX-ACCESS	read-only
			STATUS	current
			::= { hmWanMbusB7 76 }

hmWanMbusB7Value23		OBJECT-TYPE
			SYNTAX	INTEGER
			MAX-ACCESS	read-only
			STATUS	current
			::= { hmWanMbusB7 77 }

hmWanMbusB7VIF24		OBJECT-TYPE
			SYNTAX	INTEGER
			MAX-ACCESS	read-only
			STATUS	current
			::= { hmWanMbusB7 78 }

hmWanMbusB7Value24		OBJECT-TYPE
			SYNTAX	INTEGER
			MAX-ACCESS	read-only
			STATUS	current
			::= { hmWanMbusB7 79 }

hmWanMbusB7VIF25		OBJECT-TYPE
			SYNTAX	INTEGER
			MAX-ACCESS	read-only
			STATUS	current
			::= { hmWanMbusB7 80 }

hmWanMbusB7Value25		OBJECT-TYPE
			SYNTAX	INTEGER
			MAX-ACCESS	read-only
			STATUS	current
			::= { hmWanMbusB7 81 }

hmWanMbusB7VIF26		OBJECT-TYPE
			SYNTAX	INTEGER
			MAX-ACCESS	read-only
			STATUS	current
			::= { hmWanMbusB7 82 }

hmWanMbusB7Value26		OBJECT-TYPE
			SYNTAX	INTEGER
			MAX-ACCESS	read-only
			STATUS	current
			::= { hmWanMbusB7 83 }

hmWanMbusB7VIF27		OBJECT-TYPE
			SYNTAX	INTEGER
			MAX-ACCESS	read-only
			STATUS	current
			::= { hmWanMbusB7 84 }

hmWanMbusB7Value27		OBJECT-TYPE
			SYNTAX	INTEGER
			MAX-ACCESS	read-only
			STATUS	current
			::= { hmWanMbusB7 85 }

hmWanMbusB7VIF28		OBJECT-TYPE
			SYNTAX	INTEGER
			MAX-ACCESS	read-only
			STATUS	current
			::= { hmWanMbusB7 86 }

hmWanMbusB7Value28		OBJECT-TYPE
			SYNTAX	INTEGER
			MAX-ACCESS	read-only
			STATUS	current
			::= { hmWanMbusB7 87 }

hmWanMbusB7VIF29		OBJECT-TYPE
			SYNTAX	INTEGER
			MAX-ACCESS	read-only
			STATUS	current
			::= { hmWanMbusB7 88 }

hmWanMbusB7Value29		OBJECT-TYPE
			SYNTAX	INTEGER
			MAX-ACCESS	read-only
			STATUS	current
			::= { hmWanMbusB7 89 }

hmWanMbusB7VIF2A		OBJECT-TYPE
			SYNTAX	INTEGER
			MAX-ACCESS	read-only
			STATUS	current
			::= { hmWanMbusB7 90 }

hmWanMbusB7Value2A		OBJECT-TYPE
			SYNTAX	INTEGER
			MAX-ACCESS	read-only
			STATUS	current
			::= { hmWanMbusB7 91 }

hmWanMbusB7VIF2B		OBJECT-TYPE
			SYNTAX	INTEGER
			MAX-ACCESS	read-only
			STATUS	current
			::= { hmWanMbusB7 92 }

hmWanMbusB7Value2B		OBJECT-TYPE
			SYNTAX	INTEGER
			MAX-ACCESS	read-only
			STATUS	current
			::= { hmWanMbusB7 93 }

hmWanMbusB7VIF2C		OBJECT-TYPE
			SYNTAX	INTEGER
			MAX-ACCESS	read-only
			STATUS	current
			::= { hmWanMbusB7 94 }

hmWanMbusB7Value2C		OBJECT-TYPE
			SYNTAX	INTEGER
			MAX-ACCESS	read-only
			STATUS	current
			::= { hmWanMbusB7 95 }

hmWanMbusB7VIF2D		OBJECT-TYPE
			SYNTAX	INTEGER
			MAX-ACCESS	read-only
			STATUS	current
			::= { hmWanMbusB7 96 }

hmWanMbusB7Value2D		OBJECT-TYPE
			SYNTAX	INTEGER
			MAX-ACCESS	read-only
			STATUS	current
			::= { hmWanMbusB7 97 }

hmWanMbusB7VIF2E		OBJECT-TYPE
			SYNTAX	INTEGER
			MAX-ACCESS	read-only
			STATUS	current
			::= { hmWanMbusB7 98 }

hmWanMbusB7Value2E		OBJECT-TYPE
			SYNTAX	INTEGER
			MAX-ACCESS	read-only
			STATUS	current
			::= { hmWanMbusB7 99 }

hmWanMbusB7VIF2F		OBJECT-TYPE
			SYNTAX	INTEGER
			MAX-ACCESS	read-only
			STATUS	current
			::= { hmWanMbusB7 100 }

hmWanMbusB7Value2F		OBJECT-TYPE
			SYNTAX	INTEGER
			MAX-ACCESS	read-only
			STATUS	current
			::= { hmWanMbusB7 101 }

hmWanMbusB8			OBJECT IDENTIFIER ::= { hmWanMbus 184 }

hmWanMbusB8IdNumber		OBJECT-TYPE
			SYNTAX	Gauge32
			MAX-ACCESS	read-only
			STATUS	current
			::= { hmWanMbusB8 1 }

hmWanMbusB8Manufacturer	OBJECT-TYPE
			SYNTAX	Gauge32
			MAX-ACCESS	read-only
			STATUS	current
			::= { hmWanMbusB8 2 }

hmWanMbusB8Version		OBJECT-TYPE
			SYNTAX	Gauge32
			MAX-ACCESS	read-only
			STATUS	current
			::= { hmWanMbusB8 3 }

hmWanMbusB8Medium		OBJECT-TYPE
			SYNTAX	Gauge32
			MAX-ACCESS	read-only
			STATUS	current
			::= { hmWanMbusB8 4 }

hmWanMbusB8Status		OBJECT-TYPE
			SYNTAX	Gauge32
			MAX-ACCESS	read-only
			STATUS	current
			::= { hmWanMbusB8 5 }

hmWanMbusB8VIF00		OBJECT-TYPE
			SYNTAX	INTEGER
			MAX-ACCESS	read-only
			STATUS	current
			::= { hmWanMbusB8 6 }

hmWanMbusB8Value00		OBJECT-TYPE
			SYNTAX	INTEGER
			MAX-ACCESS	read-only
			STATUS	current
			::= { hmWanMbusB8 7 }

hmWanMbusB8VIF01		OBJECT-TYPE
			SYNTAX	INTEGER
			MAX-ACCESS	read-only
			STATUS	current
			::= { hmWanMbusB8 8 }

hmWanMbusB8Value01		OBJECT-TYPE
			SYNTAX	INTEGER
			MAX-ACCESS	read-only
			STATUS	current
			::= { hmWanMbusB8 9 }

hmWanMbusB8VIF02		OBJECT-TYPE
			SYNTAX	INTEGER
			MAX-ACCESS	read-only
			STATUS	current
			::= { hmWanMbusB8 10 }

hmWanMbusB8Value02		OBJECT-TYPE
			SYNTAX	INTEGER
			MAX-ACCESS	read-only
			STATUS	current
			::= { hmWanMbusB8 11 }

hmWanMbusB8VIF03		OBJECT-TYPE
			SYNTAX	INTEGER
			MAX-ACCESS	read-only
			STATUS	current
			::= { hmWanMbusB8 12 }

hmWanMbusB8Value03		OBJECT-TYPE
			SYNTAX	INTEGER
			MAX-ACCESS	read-only
			STATUS	current
			::= { hmWanMbusB8 13 }

hmWanMbusB8VIF04		OBJECT-TYPE
			SYNTAX	INTEGER
			MAX-ACCESS	read-only
			STATUS	current
			::= { hmWanMbusB8 14 }

hmWanMbusB8Value04		OBJECT-TYPE
			SYNTAX	INTEGER
			MAX-ACCESS	read-only
			STATUS	current
			::= { hmWanMbusB8 15 }

hmWanMbusB8VIF05		OBJECT-TYPE
			SYNTAX	INTEGER
			MAX-ACCESS	read-only
			STATUS	current
			::= { hmWanMbusB8 16 }

hmWanMbusB8Value05		OBJECT-TYPE
			SYNTAX	INTEGER
			MAX-ACCESS	read-only
			STATUS	current
			::= { hmWanMbusB8 17 }

hmWanMbusB8VIF06		OBJECT-TYPE
			SYNTAX	INTEGER
			MAX-ACCESS	read-only
			STATUS	current
			::= { hmWanMbusB8 18 }

hmWanMbusB8Value06		OBJECT-TYPE
			SYNTAX	INTEGER
			MAX-ACCESS	read-only
			STATUS	current
			::= { hmWanMbusB8 19 }

hmWanMbusB8VIF07		OBJECT-TYPE
			SYNTAX	INTEGER
			MAX-ACCESS	read-only
			STATUS	current
			::= { hmWanMbusB8 20 }

hmWanMbusB8Value07		OBJECT-TYPE
			SYNTAX	INTEGER
			MAX-ACCESS	read-only
			STATUS	current
			::= { hmWanMbusB8 21 }

hmWanMbusB8VIF08		OBJECT-TYPE
			SYNTAX	INTEGER
			MAX-ACCESS	read-only
			STATUS	current
			::= { hmWanMbusB8 22 }

hmWanMbusB8Value08		OBJECT-TYPE
			SYNTAX	INTEGER
			MAX-ACCESS	read-only
			STATUS	current
			::= { hmWanMbusB8 23 }

hmWanMbusB8VIF09		OBJECT-TYPE
			SYNTAX	INTEGER
			MAX-ACCESS	read-only
			STATUS	current
			::= { hmWanMbusB8 24 }

hmWanMbusB8Value09		OBJECT-TYPE
			SYNTAX	INTEGER
			MAX-ACCESS	read-only
			STATUS	current
			::= { hmWanMbusB8 25 }

hmWanMbusB8VIF0A		OBJECT-TYPE
			SYNTAX	INTEGER
			MAX-ACCESS	read-only
			STATUS	current
			::= { hmWanMbusB8 26 }

hmWanMbusB8Value0A		OBJECT-TYPE
			SYNTAX	INTEGER
			MAX-ACCESS	read-only
			STATUS	current
			::= { hmWanMbusB8 27 }

hmWanMbusB8VIF0B		OBJECT-TYPE
			SYNTAX	INTEGER
			MAX-ACCESS	read-only
			STATUS	current
			::= { hmWanMbusB8 28 }

hmWanMbusB8Value0B		OBJECT-TYPE
			SYNTAX	INTEGER
			MAX-ACCESS	read-only
			STATUS	current
			::= { hmWanMbusB8 29 }

hmWanMbusB8VIF0C		OBJECT-TYPE
			SYNTAX	INTEGER
			MAX-ACCESS	read-only
			STATUS	current
			::= { hmWanMbusB8 30 }

hmWanMbusB8Value0C		OBJECT-TYPE
			SYNTAX	INTEGER
			MAX-ACCESS	read-only
			STATUS	current
			::= { hmWanMbusB8 31 }

hmWanMbusB8VIF0D		OBJECT-TYPE
			SYNTAX	INTEGER
			MAX-ACCESS	read-only
			STATUS	current
			::= { hmWanMbusB8 32 }

hmWanMbusB8Value0D		OBJECT-TYPE
			SYNTAX	INTEGER
			MAX-ACCESS	read-only
			STATUS	current
			::= { hmWanMbusB8 33 }

hmWanMbusB8VIF0E		OBJECT-TYPE
			SYNTAX	INTEGER
			MAX-ACCESS	read-only
			STATUS	current
			::= { hmWanMbusB8 34 }

hmWanMbusB8Value0E		OBJECT-TYPE
			SYNTAX	INTEGER
			MAX-ACCESS	read-only
			STATUS	current
			::= { hmWanMbusB8 35 }

hmWanMbusB8VIF0F		OBJECT-TYPE
			SYNTAX	INTEGER
			MAX-ACCESS	read-only
			STATUS	current
			::= { hmWanMbusB8 36 }

hmWanMbusB8Value0F		OBJECT-TYPE
			SYNTAX	INTEGER
			MAX-ACCESS	read-only
			STATUS	current
			::= { hmWanMbusB8 37 }

hmWanMbusB8VIF10		OBJECT-TYPE
			SYNTAX	INTEGER
			MAX-ACCESS	read-only
			STATUS	current
			::= { hmWanMbusB8 38 }

hmWanMbusB8Value10		OBJECT-TYPE
			SYNTAX	INTEGER
			MAX-ACCESS	read-only
			STATUS	current
			::= { hmWanMbusB8 39 }

hmWanMbusB8VIF11		OBJECT-TYPE
			SYNTAX	INTEGER
			MAX-ACCESS	read-only
			STATUS	current
			::= { hmWanMbusB8 40 }

hmWanMbusB8Value11		OBJECT-TYPE
			SYNTAX	INTEGER
			MAX-ACCESS	read-only
			STATUS	current
			::= { hmWanMbusB8 41 }

hmWanMbusB8VIF12		OBJECT-TYPE
			SYNTAX	INTEGER
			MAX-ACCESS	read-only
			STATUS	current
			::= { hmWanMbusB8 42 }

hmWanMbusB8Value12		OBJECT-TYPE
			SYNTAX	INTEGER
			MAX-ACCESS	read-only
			STATUS	current
			::= { hmWanMbusB8 43 }

hmWanMbusB8VIF13		OBJECT-TYPE
			SYNTAX	INTEGER
			MAX-ACCESS	read-only
			STATUS	current
			::= { hmWanMbusB8 44 }

hmWanMbusB8Value13		OBJECT-TYPE
			SYNTAX	INTEGER
			MAX-ACCESS	read-only
			STATUS	current
			::= { hmWanMbusB8 45 }

hmWanMbusB8VIF14		OBJECT-TYPE
			SYNTAX	INTEGER
			MAX-ACCESS	read-only
			STATUS	current
			::= { hmWanMbusB8 46 }

hmWanMbusB8Value14		OBJECT-TYPE
			SYNTAX	INTEGER
			MAX-ACCESS	read-only
			STATUS	current
			::= { hmWanMbusB8 47 }

hmWanMbusB8VIF15		OBJECT-TYPE
			SYNTAX	INTEGER
			MAX-ACCESS	read-only
			STATUS	current
			::= { hmWanMbusB8 48 }

hmWanMbusB8Value15		OBJECT-TYPE
			SYNTAX	INTEGER
			MAX-ACCESS	read-only
			STATUS	current
			::= { hmWanMbusB8 49 }

hmWanMbusB8VIF16		OBJECT-TYPE
			SYNTAX	INTEGER
			MAX-ACCESS	read-only
			STATUS	current
			::= { hmWanMbusB8 50 }

hmWanMbusB8Value16		OBJECT-TYPE
			SYNTAX	INTEGER
			MAX-ACCESS	read-only
			STATUS	current
			::= { hmWanMbusB8 51 }

hmWanMbusB8VIF17		OBJECT-TYPE
			SYNTAX	INTEGER
			MAX-ACCESS	read-only
			STATUS	current
			::= { hmWanMbusB8 52 }

hmWanMbusB8Value17		OBJECT-TYPE
			SYNTAX	INTEGER
			MAX-ACCESS	read-only
			STATUS	current
			::= { hmWanMbusB8 53 }

hmWanMbusB8VIF18		OBJECT-TYPE
			SYNTAX	INTEGER
			MAX-ACCESS	read-only
			STATUS	current
			::= { hmWanMbusB8 54 }

hmWanMbusB8Value18		OBJECT-TYPE
			SYNTAX	INTEGER
			MAX-ACCESS	read-only
			STATUS	current
			::= { hmWanMbusB8 55 }

hmWanMbusB8VIF19		OBJECT-TYPE
			SYNTAX	INTEGER
			MAX-ACCESS	read-only
			STATUS	current
			::= { hmWanMbusB8 56 }

hmWanMbusB8Value19		OBJECT-TYPE
			SYNTAX	INTEGER
			MAX-ACCESS	read-only
			STATUS	current
			::= { hmWanMbusB8 57 }

hmWanMbusB8VIF1A		OBJECT-TYPE
			SYNTAX	INTEGER
			MAX-ACCESS	read-only
			STATUS	current
			::= { hmWanMbusB8 58 }

hmWanMbusB8Value1A		OBJECT-TYPE
			SYNTAX	INTEGER
			MAX-ACCESS	read-only
			STATUS	current
			::= { hmWanMbusB8 59 }

hmWanMbusB8VIF1B		OBJECT-TYPE
			SYNTAX	INTEGER
			MAX-ACCESS	read-only
			STATUS	current
			::= { hmWanMbusB8 60 }

hmWanMbusB8Value1B		OBJECT-TYPE
			SYNTAX	INTEGER
			MAX-ACCESS	read-only
			STATUS	current
			::= { hmWanMbusB8 61 }

hmWanMbusB8VIF1C		OBJECT-TYPE
			SYNTAX	INTEGER
			MAX-ACCESS	read-only
			STATUS	current
			::= { hmWanMbusB8 62 }

hmWanMbusB8Value1C		OBJECT-TYPE
			SYNTAX	INTEGER
			MAX-ACCESS	read-only
			STATUS	current
			::= { hmWanMbusB8 63 }

hmWanMbusB8VIF1D		OBJECT-TYPE
			SYNTAX	INTEGER
			MAX-ACCESS	read-only
			STATUS	current
			::= { hmWanMbusB8 64 }

hmWanMbusB8Value1D		OBJECT-TYPE
			SYNTAX	INTEGER
			MAX-ACCESS	read-only
			STATUS	current
			::= { hmWanMbusB8 65 }

hmWanMbusB8VIF1E		OBJECT-TYPE
			SYNTAX	INTEGER
			MAX-ACCESS	read-only
			STATUS	current
			::= { hmWanMbusB8 66 }

hmWanMbusB8Value1E		OBJECT-TYPE
			SYNTAX	INTEGER
			MAX-ACCESS	read-only
			STATUS	current
			::= { hmWanMbusB8 67 }

hmWanMbusB8VIF1F		OBJECT-TYPE
			SYNTAX	INTEGER
			MAX-ACCESS	read-only
			STATUS	current
			::= { hmWanMbusB8 68 }

hmWanMbusB8Value1F		OBJECT-TYPE
			SYNTAX	INTEGER
			MAX-ACCESS	read-only
			STATUS	current
			::= { hmWanMbusB8 69 }

hmWanMbusB8VIF20		OBJECT-TYPE
			SYNTAX	INTEGER
			MAX-ACCESS	read-only
			STATUS	current
			::= { hmWanMbusB8 70 }

hmWanMbusB8Value20		OBJECT-TYPE
			SYNTAX	INTEGER
			MAX-ACCESS	read-only
			STATUS	current
			::= { hmWanMbusB8 71 }

hmWanMbusB8VIF21		OBJECT-TYPE
			SYNTAX	INTEGER
			MAX-ACCESS	read-only
			STATUS	current
			::= { hmWanMbusB8 72 }

hmWanMbusB8Value21		OBJECT-TYPE
			SYNTAX	INTEGER
			MAX-ACCESS	read-only
			STATUS	current
			::= { hmWanMbusB8 73 }

hmWanMbusB8VIF22		OBJECT-TYPE
			SYNTAX	INTEGER
			MAX-ACCESS	read-only
			STATUS	current
			::= { hmWanMbusB8 74 }

hmWanMbusB8Value22		OBJECT-TYPE
			SYNTAX	INTEGER
			MAX-ACCESS	read-only
			STATUS	current
			::= { hmWanMbusB8 75 }

hmWanMbusB8VIF23		OBJECT-TYPE
			SYNTAX	INTEGER
			MAX-ACCESS	read-only
			STATUS	current
			::= { hmWanMbusB8 76 }

hmWanMbusB8Value23		OBJECT-TYPE
			SYNTAX	INTEGER
			MAX-ACCESS	read-only
			STATUS	current
			::= { hmWanMbusB8 77 }

hmWanMbusB8VIF24		OBJECT-TYPE
			SYNTAX	INTEGER
			MAX-ACCESS	read-only
			STATUS	current
			::= { hmWanMbusB8 78 }

hmWanMbusB8Value24		OBJECT-TYPE
			SYNTAX	INTEGER
			MAX-ACCESS	read-only
			STATUS	current
			::= { hmWanMbusB8 79 }

hmWanMbusB8VIF25		OBJECT-TYPE
			SYNTAX	INTEGER
			MAX-ACCESS	read-only
			STATUS	current
			::= { hmWanMbusB8 80 }

hmWanMbusB8Value25		OBJECT-TYPE
			SYNTAX	INTEGER
			MAX-ACCESS	read-only
			STATUS	current
			::= { hmWanMbusB8 81 }

hmWanMbusB8VIF26		OBJECT-TYPE
			SYNTAX	INTEGER
			MAX-ACCESS	read-only
			STATUS	current
			::= { hmWanMbusB8 82 }

hmWanMbusB8Value26		OBJECT-TYPE
			SYNTAX	INTEGER
			MAX-ACCESS	read-only
			STATUS	current
			::= { hmWanMbusB8 83 }

hmWanMbusB8VIF27		OBJECT-TYPE
			SYNTAX	INTEGER
			MAX-ACCESS	read-only
			STATUS	current
			::= { hmWanMbusB8 84 }

hmWanMbusB8Value27		OBJECT-TYPE
			SYNTAX	INTEGER
			MAX-ACCESS	read-only
			STATUS	current
			::= { hmWanMbusB8 85 }

hmWanMbusB8VIF28		OBJECT-TYPE
			SYNTAX	INTEGER
			MAX-ACCESS	read-only
			STATUS	current
			::= { hmWanMbusB8 86 }

hmWanMbusB8Value28		OBJECT-TYPE
			SYNTAX	INTEGER
			MAX-ACCESS	read-only
			STATUS	current
			::= { hmWanMbusB8 87 }

hmWanMbusB8VIF29		OBJECT-TYPE
			SYNTAX	INTEGER
			MAX-ACCESS	read-only
			STATUS	current
			::= { hmWanMbusB8 88 }

hmWanMbusB8Value29		OBJECT-TYPE
			SYNTAX	INTEGER
			MAX-ACCESS	read-only
			STATUS	current
			::= { hmWanMbusB8 89 }

hmWanMbusB8VIF2A		OBJECT-TYPE
			SYNTAX	INTEGER
			MAX-ACCESS	read-only
			STATUS	current
			::= { hmWanMbusB8 90 }

hmWanMbusB8Value2A		OBJECT-TYPE
			SYNTAX	INTEGER
			MAX-ACCESS	read-only
			STATUS	current
			::= { hmWanMbusB8 91 }

hmWanMbusB8VIF2B		OBJECT-TYPE
			SYNTAX	INTEGER
			MAX-ACCESS	read-only
			STATUS	current
			::= { hmWanMbusB8 92 }

hmWanMbusB8Value2B		OBJECT-TYPE
			SYNTAX	INTEGER
			MAX-ACCESS	read-only
			STATUS	current
			::= { hmWanMbusB8 93 }

hmWanMbusB8VIF2C		OBJECT-TYPE
			SYNTAX	INTEGER
			MAX-ACCESS	read-only
			STATUS	current
			::= { hmWanMbusB8 94 }

hmWanMbusB8Value2C		OBJECT-TYPE
			SYNTAX	INTEGER
			MAX-ACCESS	read-only
			STATUS	current
			::= { hmWanMbusB8 95 }

hmWanMbusB8VIF2D		OBJECT-TYPE
			SYNTAX	INTEGER
			MAX-ACCESS	read-only
			STATUS	current
			::= { hmWanMbusB8 96 }

hmWanMbusB8Value2D		OBJECT-TYPE
			SYNTAX	INTEGER
			MAX-ACCESS	read-only
			STATUS	current
			::= { hmWanMbusB8 97 }

hmWanMbusB8VIF2E		OBJECT-TYPE
			SYNTAX	INTEGER
			MAX-ACCESS	read-only
			STATUS	current
			::= { hmWanMbusB8 98 }

hmWanMbusB8Value2E		OBJECT-TYPE
			SYNTAX	INTEGER
			MAX-ACCESS	read-only
			STATUS	current
			::= { hmWanMbusB8 99 }

hmWanMbusB8VIF2F		OBJECT-TYPE
			SYNTAX	INTEGER
			MAX-ACCESS	read-only
			STATUS	current
			::= { hmWanMbusB8 100 }

hmWanMbusB8Value2F		OBJECT-TYPE
			SYNTAX	INTEGER
			MAX-ACCESS	read-only
			STATUS	current
			::= { hmWanMbusB8 101 }

hmWanMbusB9			OBJECT IDENTIFIER ::= { hmWanMbus 185 }

hmWanMbusB9IdNumber		OBJECT-TYPE
			SYNTAX	Gauge32
			MAX-ACCESS	read-only
			STATUS	current
			::= { hmWanMbusB9 1 }

hmWanMbusB9Manufacturer	OBJECT-TYPE
			SYNTAX	Gauge32
			MAX-ACCESS	read-only
			STATUS	current
			::= { hmWanMbusB9 2 }

hmWanMbusB9Version		OBJECT-TYPE
			SYNTAX	Gauge32
			MAX-ACCESS	read-only
			STATUS	current
			::= { hmWanMbusB9 3 }

hmWanMbusB9Medium		OBJECT-TYPE
			SYNTAX	Gauge32
			MAX-ACCESS	read-only
			STATUS	current
			::= { hmWanMbusB9 4 }

hmWanMbusB9Status		OBJECT-TYPE
			SYNTAX	Gauge32
			MAX-ACCESS	read-only
			STATUS	current
			::= { hmWanMbusB9 5 }

hmWanMbusB9VIF00		OBJECT-TYPE
			SYNTAX	INTEGER
			MAX-ACCESS	read-only
			STATUS	current
			::= { hmWanMbusB9 6 }

hmWanMbusB9Value00		OBJECT-TYPE
			SYNTAX	INTEGER
			MAX-ACCESS	read-only
			STATUS	current
			::= { hmWanMbusB9 7 }

hmWanMbusB9VIF01		OBJECT-TYPE
			SYNTAX	INTEGER
			MAX-ACCESS	read-only
			STATUS	current
			::= { hmWanMbusB9 8 }

hmWanMbusB9Value01		OBJECT-TYPE
			SYNTAX	INTEGER
			MAX-ACCESS	read-only
			STATUS	current
			::= { hmWanMbusB9 9 }

hmWanMbusB9VIF02		OBJECT-TYPE
			SYNTAX	INTEGER
			MAX-ACCESS	read-only
			STATUS	current
			::= { hmWanMbusB9 10 }

hmWanMbusB9Value02		OBJECT-TYPE
			SYNTAX	INTEGER
			MAX-ACCESS	read-only
			STATUS	current
			::= { hmWanMbusB9 11 }

hmWanMbusB9VIF03		OBJECT-TYPE
			SYNTAX	INTEGER
			MAX-ACCESS	read-only
			STATUS	current
			::= { hmWanMbusB9 12 }

hmWanMbusB9Value03		OBJECT-TYPE
			SYNTAX	INTEGER
			MAX-ACCESS	read-only
			STATUS	current
			::= { hmWanMbusB9 13 }

hmWanMbusB9VIF04		OBJECT-TYPE
			SYNTAX	INTEGER
			MAX-ACCESS	read-only
			STATUS	current
			::= { hmWanMbusB9 14 }

hmWanMbusB9Value04		OBJECT-TYPE
			SYNTAX	INTEGER
			MAX-ACCESS	read-only
			STATUS	current
			::= { hmWanMbusB9 15 }

hmWanMbusB9VIF05		OBJECT-TYPE
			SYNTAX	INTEGER
			MAX-ACCESS	read-only
			STATUS	current
			::= { hmWanMbusB9 16 }

hmWanMbusB9Value05		OBJECT-TYPE
			SYNTAX	INTEGER
			MAX-ACCESS	read-only
			STATUS	current
			::= { hmWanMbusB9 17 }

hmWanMbusB9VIF06		OBJECT-TYPE
			SYNTAX	INTEGER
			MAX-ACCESS	read-only
			STATUS	current
			::= { hmWanMbusB9 18 }

hmWanMbusB9Value06		OBJECT-TYPE
			SYNTAX	INTEGER
			MAX-ACCESS	read-only
			STATUS	current
			::= { hmWanMbusB9 19 }

hmWanMbusB9VIF07		OBJECT-TYPE
			SYNTAX	INTEGER
			MAX-ACCESS	read-only
			STATUS	current
			::= { hmWanMbusB9 20 }

hmWanMbusB9Value07		OBJECT-TYPE
			SYNTAX	INTEGER
			MAX-ACCESS	read-only
			STATUS	current
			::= { hmWanMbusB9 21 }

hmWanMbusB9VIF08		OBJECT-TYPE
			SYNTAX	INTEGER
			MAX-ACCESS	read-only
			STATUS	current
			::= { hmWanMbusB9 22 }

hmWanMbusB9Value08		OBJECT-TYPE
			SYNTAX	INTEGER
			MAX-ACCESS	read-only
			STATUS	current
			::= { hmWanMbusB9 23 }

hmWanMbusB9VIF09		OBJECT-TYPE
			SYNTAX	INTEGER
			MAX-ACCESS	read-only
			STATUS	current
			::= { hmWanMbusB9 24 }

hmWanMbusB9Value09		OBJECT-TYPE
			SYNTAX	INTEGER
			MAX-ACCESS	read-only
			STATUS	current
			::= { hmWanMbusB9 25 }

hmWanMbusB9VIF0A		OBJECT-TYPE
			SYNTAX	INTEGER
			MAX-ACCESS	read-only
			STATUS	current
			::= { hmWanMbusB9 26 }

hmWanMbusB9Value0A		OBJECT-TYPE
			SYNTAX	INTEGER
			MAX-ACCESS	read-only
			STATUS	current
			::= { hmWanMbusB9 27 }

hmWanMbusB9VIF0B		OBJECT-TYPE
			SYNTAX	INTEGER
			MAX-ACCESS	read-only
			STATUS	current
			::= { hmWanMbusB9 28 }

hmWanMbusB9Value0B		OBJECT-TYPE
			SYNTAX	INTEGER
			MAX-ACCESS	read-only
			STATUS	current
			::= { hmWanMbusB9 29 }

hmWanMbusB9VIF0C		OBJECT-TYPE
			SYNTAX	INTEGER
			MAX-ACCESS	read-only
			STATUS	current
			::= { hmWanMbusB9 30 }

hmWanMbusB9Value0C		OBJECT-TYPE
			SYNTAX	INTEGER
			MAX-ACCESS	read-only
			STATUS	current
			::= { hmWanMbusB9 31 }

hmWanMbusB9VIF0D		OBJECT-TYPE
			SYNTAX	INTEGER
			MAX-ACCESS	read-only
			STATUS	current
			::= { hmWanMbusB9 32 }

hmWanMbusB9Value0D		OBJECT-TYPE
			SYNTAX	INTEGER
			MAX-ACCESS	read-only
			STATUS	current
			::= { hmWanMbusB9 33 }

hmWanMbusB9VIF0E		OBJECT-TYPE
			SYNTAX	INTEGER
			MAX-ACCESS	read-only
			STATUS	current
			::= { hmWanMbusB9 34 }

hmWanMbusB9Value0E		OBJECT-TYPE
			SYNTAX	INTEGER
			MAX-ACCESS	read-only
			STATUS	current
			::= { hmWanMbusB9 35 }

hmWanMbusB9VIF0F		OBJECT-TYPE
			SYNTAX	INTEGER
			MAX-ACCESS	read-only
			STATUS	current
			::= { hmWanMbusB9 36 }

hmWanMbusB9Value0F		OBJECT-TYPE
			SYNTAX	INTEGER
			MAX-ACCESS	read-only
			STATUS	current
			::= { hmWanMbusB9 37 }

hmWanMbusB9VIF10		OBJECT-TYPE
			SYNTAX	INTEGER
			MAX-ACCESS	read-only
			STATUS	current
			::= { hmWanMbusB9 38 }

hmWanMbusB9Value10		OBJECT-TYPE
			SYNTAX	INTEGER
			MAX-ACCESS	read-only
			STATUS	current
			::= { hmWanMbusB9 39 }

hmWanMbusB9VIF11		OBJECT-TYPE
			SYNTAX	INTEGER
			MAX-ACCESS	read-only
			STATUS	current
			::= { hmWanMbusB9 40 }

hmWanMbusB9Value11		OBJECT-TYPE
			SYNTAX	INTEGER
			MAX-ACCESS	read-only
			STATUS	current
			::= { hmWanMbusB9 41 }

hmWanMbusB9VIF12		OBJECT-TYPE
			SYNTAX	INTEGER
			MAX-ACCESS	read-only
			STATUS	current
			::= { hmWanMbusB9 42 }

hmWanMbusB9Value12		OBJECT-TYPE
			SYNTAX	INTEGER
			MAX-ACCESS	read-only
			STATUS	current
			::= { hmWanMbusB9 43 }

hmWanMbusB9VIF13		OBJECT-TYPE
			SYNTAX	INTEGER
			MAX-ACCESS	read-only
			STATUS	current
			::= { hmWanMbusB9 44 }

hmWanMbusB9Value13		OBJECT-TYPE
			SYNTAX	INTEGER
			MAX-ACCESS	read-only
			STATUS	current
			::= { hmWanMbusB9 45 }

hmWanMbusB9VIF14		OBJECT-TYPE
			SYNTAX	INTEGER
			MAX-ACCESS	read-only
			STATUS	current
			::= { hmWanMbusB9 46 }

hmWanMbusB9Value14		OBJECT-TYPE
			SYNTAX	INTEGER
			MAX-ACCESS	read-only
			STATUS	current
			::= { hmWanMbusB9 47 }

hmWanMbusB9VIF15		OBJECT-TYPE
			SYNTAX	INTEGER
			MAX-ACCESS	read-only
			STATUS	current
			::= { hmWanMbusB9 48 }

hmWanMbusB9Value15		OBJECT-TYPE
			SYNTAX	INTEGER
			MAX-ACCESS	read-only
			STATUS	current
			::= { hmWanMbusB9 49 }

hmWanMbusB9VIF16		OBJECT-TYPE
			SYNTAX	INTEGER
			MAX-ACCESS	read-only
			STATUS	current
			::= { hmWanMbusB9 50 }

hmWanMbusB9Value16		OBJECT-TYPE
			SYNTAX	INTEGER
			MAX-ACCESS	read-only
			STATUS	current
			::= { hmWanMbusB9 51 }

hmWanMbusB9VIF17		OBJECT-TYPE
			SYNTAX	INTEGER
			MAX-ACCESS	read-only
			STATUS	current
			::= { hmWanMbusB9 52 }

hmWanMbusB9Value17		OBJECT-TYPE
			SYNTAX	INTEGER
			MAX-ACCESS	read-only
			STATUS	current
			::= { hmWanMbusB9 53 }

hmWanMbusB9VIF18		OBJECT-TYPE
			SYNTAX	INTEGER
			MAX-ACCESS	read-only
			STATUS	current
			::= { hmWanMbusB9 54 }

hmWanMbusB9Value18		OBJECT-TYPE
			SYNTAX	INTEGER
			MAX-ACCESS	read-only
			STATUS	current
			::= { hmWanMbusB9 55 }

hmWanMbusB9VIF19		OBJECT-TYPE
			SYNTAX	INTEGER
			MAX-ACCESS	read-only
			STATUS	current
			::= { hmWanMbusB9 56 }

hmWanMbusB9Value19		OBJECT-TYPE
			SYNTAX	INTEGER
			MAX-ACCESS	read-only
			STATUS	current
			::= { hmWanMbusB9 57 }

hmWanMbusB9VIF1A		OBJECT-TYPE
			SYNTAX	INTEGER
			MAX-ACCESS	read-only
			STATUS	current
			::= { hmWanMbusB9 58 }

hmWanMbusB9Value1A		OBJECT-TYPE
			SYNTAX	INTEGER
			MAX-ACCESS	read-only
			STATUS	current
			::= { hmWanMbusB9 59 }

hmWanMbusB9VIF1B		OBJECT-TYPE
			SYNTAX	INTEGER
			MAX-ACCESS	read-only
			STATUS	current
			::= { hmWanMbusB9 60 }

hmWanMbusB9Value1B		OBJECT-TYPE
			SYNTAX	INTEGER
			MAX-ACCESS	read-only
			STATUS	current
			::= { hmWanMbusB9 61 }

hmWanMbusB9VIF1C		OBJECT-TYPE
			SYNTAX	INTEGER
			MAX-ACCESS	read-only
			STATUS	current
			::= { hmWanMbusB9 62 }

hmWanMbusB9Value1C		OBJECT-TYPE
			SYNTAX	INTEGER
			MAX-ACCESS	read-only
			STATUS	current
			::= { hmWanMbusB9 63 }

hmWanMbusB9VIF1D		OBJECT-TYPE
			SYNTAX	INTEGER
			MAX-ACCESS	read-only
			STATUS	current
			::= { hmWanMbusB9 64 }

hmWanMbusB9Value1D		OBJECT-TYPE
			SYNTAX	INTEGER
			MAX-ACCESS	read-only
			STATUS	current
			::= { hmWanMbusB9 65 }

hmWanMbusB9VIF1E		OBJECT-TYPE
			SYNTAX	INTEGER
			MAX-ACCESS	read-only
			STATUS	current
			::= { hmWanMbusB9 66 }

hmWanMbusB9Value1E		OBJECT-TYPE
			SYNTAX	INTEGER
			MAX-ACCESS	read-only
			STATUS	current
			::= { hmWanMbusB9 67 }

hmWanMbusB9VIF1F		OBJECT-TYPE
			SYNTAX	INTEGER
			MAX-ACCESS	read-only
			STATUS	current
			::= { hmWanMbusB9 68 }

hmWanMbusB9Value1F		OBJECT-TYPE
			SYNTAX	INTEGER
			MAX-ACCESS	read-only
			STATUS	current
			::= { hmWanMbusB9 69 }

hmWanMbusB9VIF20		OBJECT-TYPE
			SYNTAX	INTEGER
			MAX-ACCESS	read-only
			STATUS	current
			::= { hmWanMbusB9 70 }

hmWanMbusB9Value20		OBJECT-TYPE
			SYNTAX	INTEGER
			MAX-ACCESS	read-only
			STATUS	current
			::= { hmWanMbusB9 71 }

hmWanMbusB9VIF21		OBJECT-TYPE
			SYNTAX	INTEGER
			MAX-ACCESS	read-only
			STATUS	current
			::= { hmWanMbusB9 72 }

hmWanMbusB9Value21		OBJECT-TYPE
			SYNTAX	INTEGER
			MAX-ACCESS	read-only
			STATUS	current
			::= { hmWanMbusB9 73 }

hmWanMbusB9VIF22		OBJECT-TYPE
			SYNTAX	INTEGER
			MAX-ACCESS	read-only
			STATUS	current
			::= { hmWanMbusB9 74 }

hmWanMbusB9Value22		OBJECT-TYPE
			SYNTAX	INTEGER
			MAX-ACCESS	read-only
			STATUS	current
			::= { hmWanMbusB9 75 }

hmWanMbusB9VIF23		OBJECT-TYPE
			SYNTAX	INTEGER
			MAX-ACCESS	read-only
			STATUS	current
			::= { hmWanMbusB9 76 }

hmWanMbusB9Value23		OBJECT-TYPE
			SYNTAX	INTEGER
			MAX-ACCESS	read-only
			STATUS	current
			::= { hmWanMbusB9 77 }

hmWanMbusB9VIF24		OBJECT-TYPE
			SYNTAX	INTEGER
			MAX-ACCESS	read-only
			STATUS	current
			::= { hmWanMbusB9 78 }

hmWanMbusB9Value24		OBJECT-TYPE
			SYNTAX	INTEGER
			MAX-ACCESS	read-only
			STATUS	current
			::= { hmWanMbusB9 79 }

hmWanMbusB9VIF25		OBJECT-TYPE
			SYNTAX	INTEGER
			MAX-ACCESS	read-only
			STATUS	current
			::= { hmWanMbusB9 80 }

hmWanMbusB9Value25		OBJECT-TYPE
			SYNTAX	INTEGER
			MAX-ACCESS	read-only
			STATUS	current
			::= { hmWanMbusB9 81 }

hmWanMbusB9VIF26		OBJECT-TYPE
			SYNTAX	INTEGER
			MAX-ACCESS	read-only
			STATUS	current
			::= { hmWanMbusB9 82 }

hmWanMbusB9Value26		OBJECT-TYPE
			SYNTAX	INTEGER
			MAX-ACCESS	read-only
			STATUS	current
			::= { hmWanMbusB9 83 }

hmWanMbusB9VIF27		OBJECT-TYPE
			SYNTAX	INTEGER
			MAX-ACCESS	read-only
			STATUS	current
			::= { hmWanMbusB9 84 }

hmWanMbusB9Value27		OBJECT-TYPE
			SYNTAX	INTEGER
			MAX-ACCESS	read-only
			STATUS	current
			::= { hmWanMbusB9 85 }

hmWanMbusB9VIF28		OBJECT-TYPE
			SYNTAX	INTEGER
			MAX-ACCESS	read-only
			STATUS	current
			::= { hmWanMbusB9 86 }

hmWanMbusB9Value28		OBJECT-TYPE
			SYNTAX	INTEGER
			MAX-ACCESS	read-only
			STATUS	current
			::= { hmWanMbusB9 87 }

hmWanMbusB9VIF29		OBJECT-TYPE
			SYNTAX	INTEGER
			MAX-ACCESS	read-only
			STATUS	current
			::= { hmWanMbusB9 88 }

hmWanMbusB9Value29		OBJECT-TYPE
			SYNTAX	INTEGER
			MAX-ACCESS	read-only
			STATUS	current
			::= { hmWanMbusB9 89 }

hmWanMbusB9VIF2A		OBJECT-TYPE
			SYNTAX	INTEGER
			MAX-ACCESS	read-only
			STATUS	current
			::= { hmWanMbusB9 90 }

hmWanMbusB9Value2A		OBJECT-TYPE
			SYNTAX	INTEGER
			MAX-ACCESS	read-only
			STATUS	current
			::= { hmWanMbusB9 91 }

hmWanMbusB9VIF2B		OBJECT-TYPE
			SYNTAX	INTEGER
			MAX-ACCESS	read-only
			STATUS	current
			::= { hmWanMbusB9 92 }

hmWanMbusB9Value2B		OBJECT-TYPE
			SYNTAX	INTEGER
			MAX-ACCESS	read-only
			STATUS	current
			::= { hmWanMbusB9 93 }

hmWanMbusB9VIF2C		OBJECT-TYPE
			SYNTAX	INTEGER
			MAX-ACCESS	read-only
			STATUS	current
			::= { hmWanMbusB9 94 }

hmWanMbusB9Value2C		OBJECT-TYPE
			SYNTAX	INTEGER
			MAX-ACCESS	read-only
			STATUS	current
			::= { hmWanMbusB9 95 }

hmWanMbusB9VIF2D		OBJECT-TYPE
			SYNTAX	INTEGER
			MAX-ACCESS	read-only
			STATUS	current
			::= { hmWanMbusB9 96 }

hmWanMbusB9Value2D		OBJECT-TYPE
			SYNTAX	INTEGER
			MAX-ACCESS	read-only
			STATUS	current
			::= { hmWanMbusB9 97 }

hmWanMbusB9VIF2E		OBJECT-TYPE
			SYNTAX	INTEGER
			MAX-ACCESS	read-only
			STATUS	current
			::= { hmWanMbusB9 98 }

hmWanMbusB9Value2E		OBJECT-TYPE
			SYNTAX	INTEGER
			MAX-ACCESS	read-only
			STATUS	current
			::= { hmWanMbusB9 99 }

hmWanMbusB9VIF2F		OBJECT-TYPE
			SYNTAX	INTEGER
			MAX-ACCESS	read-only
			STATUS	current
			::= { hmWanMbusB9 100 }

hmWanMbusB9Value2F		OBJECT-TYPE
			SYNTAX	INTEGER
			MAX-ACCESS	read-only
			STATUS	current
			::= { hmWanMbusB9 101 }

hmWanMbusBA			OBJECT IDENTIFIER ::= { hmWanMbus 186 }

hmWanMbusBAIdNumber		OBJECT-TYPE
			SYNTAX	Gauge32
			MAX-ACCESS	read-only
			STATUS	current
			::= { hmWanMbusBA 1 }

hmWanMbusBAManufacturer	OBJECT-TYPE
			SYNTAX	Gauge32
			MAX-ACCESS	read-only
			STATUS	current
			::= { hmWanMbusBA 2 }

hmWanMbusBAVersion		OBJECT-TYPE
			SYNTAX	Gauge32
			MAX-ACCESS	read-only
			STATUS	current
			::= { hmWanMbusBA 3 }

hmWanMbusBAMedium		OBJECT-TYPE
			SYNTAX	Gauge32
			MAX-ACCESS	read-only
			STATUS	current
			::= { hmWanMbusBA 4 }

hmWanMbusBAStatus		OBJECT-TYPE
			SYNTAX	Gauge32
			MAX-ACCESS	read-only
			STATUS	current
			::= { hmWanMbusBA 5 }

hmWanMbusBAVIF00		OBJECT-TYPE
			SYNTAX	INTEGER
			MAX-ACCESS	read-only
			STATUS	current
			::= { hmWanMbusBA 6 }

hmWanMbusBAValue00		OBJECT-TYPE
			SYNTAX	INTEGER
			MAX-ACCESS	read-only
			STATUS	current
			::= { hmWanMbusBA 7 }

hmWanMbusBAVIF01		OBJECT-TYPE
			SYNTAX	INTEGER
			MAX-ACCESS	read-only
			STATUS	current
			::= { hmWanMbusBA 8 }

hmWanMbusBAValue01		OBJECT-TYPE
			SYNTAX	INTEGER
			MAX-ACCESS	read-only
			STATUS	current
			::= { hmWanMbusBA 9 }

hmWanMbusBAVIF02		OBJECT-TYPE
			SYNTAX	INTEGER
			MAX-ACCESS	read-only
			STATUS	current
			::= { hmWanMbusBA 10 }

hmWanMbusBAValue02		OBJECT-TYPE
			SYNTAX	INTEGER
			MAX-ACCESS	read-only
			STATUS	current
			::= { hmWanMbusBA 11 }

hmWanMbusBAVIF03		OBJECT-TYPE
			SYNTAX	INTEGER
			MAX-ACCESS	read-only
			STATUS	current
			::= { hmWanMbusBA 12 }

hmWanMbusBAValue03		OBJECT-TYPE
			SYNTAX	INTEGER
			MAX-ACCESS	read-only
			STATUS	current
			::= { hmWanMbusBA 13 }

hmWanMbusBAVIF04		OBJECT-TYPE
			SYNTAX	INTEGER
			MAX-ACCESS	read-only
			STATUS	current
			::= { hmWanMbusBA 14 }

hmWanMbusBAValue04		OBJECT-TYPE
			SYNTAX	INTEGER
			MAX-ACCESS	read-only
			STATUS	current
			::= { hmWanMbusBA 15 }

hmWanMbusBAVIF05		OBJECT-TYPE
			SYNTAX	INTEGER
			MAX-ACCESS	read-only
			STATUS	current
			::= { hmWanMbusBA 16 }

hmWanMbusBAValue05		OBJECT-TYPE
			SYNTAX	INTEGER
			MAX-ACCESS	read-only
			STATUS	current
			::= { hmWanMbusBA 17 }

hmWanMbusBAVIF06		OBJECT-TYPE
			SYNTAX	INTEGER
			MAX-ACCESS	read-only
			STATUS	current
			::= { hmWanMbusBA 18 }

hmWanMbusBAValue06		OBJECT-TYPE
			SYNTAX	INTEGER
			MAX-ACCESS	read-only
			STATUS	current
			::= { hmWanMbusBA 19 }

hmWanMbusBAVIF07		OBJECT-TYPE
			SYNTAX	INTEGER
			MAX-ACCESS	read-only
			STATUS	current
			::= { hmWanMbusBA 20 }

hmWanMbusBAValue07		OBJECT-TYPE
			SYNTAX	INTEGER
			MAX-ACCESS	read-only
			STATUS	current
			::= { hmWanMbusBA 21 }

hmWanMbusBAVIF08		OBJECT-TYPE
			SYNTAX	INTEGER
			MAX-ACCESS	read-only
			STATUS	current
			::= { hmWanMbusBA 22 }

hmWanMbusBAValue08		OBJECT-TYPE
			SYNTAX	INTEGER
			MAX-ACCESS	read-only
			STATUS	current
			::= { hmWanMbusBA 23 }

hmWanMbusBAVIF09		OBJECT-TYPE
			SYNTAX	INTEGER
			MAX-ACCESS	read-only
			STATUS	current
			::= { hmWanMbusBA 24 }

hmWanMbusBAValue09		OBJECT-TYPE
			SYNTAX	INTEGER
			MAX-ACCESS	read-only
			STATUS	current
			::= { hmWanMbusBA 25 }

hmWanMbusBAVIF0A		OBJECT-TYPE
			SYNTAX	INTEGER
			MAX-ACCESS	read-only
			STATUS	current
			::= { hmWanMbusBA 26 }

hmWanMbusBAValue0A		OBJECT-TYPE
			SYNTAX	INTEGER
			MAX-ACCESS	read-only
			STATUS	current
			::= { hmWanMbusBA 27 }

hmWanMbusBAVIF0B		OBJECT-TYPE
			SYNTAX	INTEGER
			MAX-ACCESS	read-only
			STATUS	current
			::= { hmWanMbusBA 28 }

hmWanMbusBAValue0B		OBJECT-TYPE
			SYNTAX	INTEGER
			MAX-ACCESS	read-only
			STATUS	current
			::= { hmWanMbusBA 29 }

hmWanMbusBAVIF0C		OBJECT-TYPE
			SYNTAX	INTEGER
			MAX-ACCESS	read-only
			STATUS	current
			::= { hmWanMbusBA 30 }

hmWanMbusBAValue0C		OBJECT-TYPE
			SYNTAX	INTEGER
			MAX-ACCESS	read-only
			STATUS	current
			::= { hmWanMbusBA 31 }

hmWanMbusBAVIF0D		OBJECT-TYPE
			SYNTAX	INTEGER
			MAX-ACCESS	read-only
			STATUS	current
			::= { hmWanMbusBA 32 }

hmWanMbusBAValue0D		OBJECT-TYPE
			SYNTAX	INTEGER
			MAX-ACCESS	read-only
			STATUS	current
			::= { hmWanMbusBA 33 }

hmWanMbusBAVIF0E		OBJECT-TYPE
			SYNTAX	INTEGER
			MAX-ACCESS	read-only
			STATUS	current
			::= { hmWanMbusBA 34 }

hmWanMbusBAValue0E		OBJECT-TYPE
			SYNTAX	INTEGER
			MAX-ACCESS	read-only
			STATUS	current
			::= { hmWanMbusBA 35 }

hmWanMbusBAVIF0F		OBJECT-TYPE
			SYNTAX	INTEGER
			MAX-ACCESS	read-only
			STATUS	current
			::= { hmWanMbusBA 36 }

hmWanMbusBAValue0F		OBJECT-TYPE
			SYNTAX	INTEGER
			MAX-ACCESS	read-only
			STATUS	current
			::= { hmWanMbusBA 37 }

hmWanMbusBAVIF10		OBJECT-TYPE
			SYNTAX	INTEGER
			MAX-ACCESS	read-only
			STATUS	current
			::= { hmWanMbusBA 38 }

hmWanMbusBAValue10		OBJECT-TYPE
			SYNTAX	INTEGER
			MAX-ACCESS	read-only
			STATUS	current
			::= { hmWanMbusBA 39 }

hmWanMbusBAVIF11		OBJECT-TYPE
			SYNTAX	INTEGER
			MAX-ACCESS	read-only
			STATUS	current
			::= { hmWanMbusBA 40 }

hmWanMbusBAValue11		OBJECT-TYPE
			SYNTAX	INTEGER
			MAX-ACCESS	read-only
			STATUS	current
			::= { hmWanMbusBA 41 }

hmWanMbusBAVIF12		OBJECT-TYPE
			SYNTAX	INTEGER
			MAX-ACCESS	read-only
			STATUS	current
			::= { hmWanMbusBA 42 }

hmWanMbusBAValue12		OBJECT-TYPE
			SYNTAX	INTEGER
			MAX-ACCESS	read-only
			STATUS	current
			::= { hmWanMbusBA 43 }

hmWanMbusBAVIF13		OBJECT-TYPE
			SYNTAX	INTEGER
			MAX-ACCESS	read-only
			STATUS	current
			::= { hmWanMbusBA 44 }

hmWanMbusBAValue13		OBJECT-TYPE
			SYNTAX	INTEGER
			MAX-ACCESS	read-only
			STATUS	current
			::= { hmWanMbusBA 45 }

hmWanMbusBAVIF14		OBJECT-TYPE
			SYNTAX	INTEGER
			MAX-ACCESS	read-only
			STATUS	current
			::= { hmWanMbusBA 46 }

hmWanMbusBAValue14		OBJECT-TYPE
			SYNTAX	INTEGER
			MAX-ACCESS	read-only
			STATUS	current
			::= { hmWanMbusBA 47 }

hmWanMbusBAVIF15		OBJECT-TYPE
			SYNTAX	INTEGER
			MAX-ACCESS	read-only
			STATUS	current
			::= { hmWanMbusBA 48 }

hmWanMbusBAValue15		OBJECT-TYPE
			SYNTAX	INTEGER
			MAX-ACCESS	read-only
			STATUS	current
			::= { hmWanMbusBA 49 }

hmWanMbusBAVIF16		OBJECT-TYPE
			SYNTAX	INTEGER
			MAX-ACCESS	read-only
			STATUS	current
			::= { hmWanMbusBA 50 }

hmWanMbusBAValue16		OBJECT-TYPE
			SYNTAX	INTEGER
			MAX-ACCESS	read-only
			STATUS	current
			::= { hmWanMbusBA 51 }

hmWanMbusBAVIF17		OBJECT-TYPE
			SYNTAX	INTEGER
			MAX-ACCESS	read-only
			STATUS	current
			::= { hmWanMbusBA 52 }

hmWanMbusBAValue17		OBJECT-TYPE
			SYNTAX	INTEGER
			MAX-ACCESS	read-only
			STATUS	current
			::= { hmWanMbusBA 53 }

hmWanMbusBAVIF18		OBJECT-TYPE
			SYNTAX	INTEGER
			MAX-ACCESS	read-only
			STATUS	current
			::= { hmWanMbusBA 54 }

hmWanMbusBAValue18		OBJECT-TYPE
			SYNTAX	INTEGER
			MAX-ACCESS	read-only
			STATUS	current
			::= { hmWanMbusBA 55 }

hmWanMbusBAVIF19		OBJECT-TYPE
			SYNTAX	INTEGER
			MAX-ACCESS	read-only
			STATUS	current
			::= { hmWanMbusBA 56 }

hmWanMbusBAValue19		OBJECT-TYPE
			SYNTAX	INTEGER
			MAX-ACCESS	read-only
			STATUS	current
			::= { hmWanMbusBA 57 }

hmWanMbusBAVIF1A		OBJECT-TYPE
			SYNTAX	INTEGER
			MAX-ACCESS	read-only
			STATUS	current
			::= { hmWanMbusBA 58 }

hmWanMbusBAValue1A		OBJECT-TYPE
			SYNTAX	INTEGER
			MAX-ACCESS	read-only
			STATUS	current
			::= { hmWanMbusBA 59 }

hmWanMbusBAVIF1B		OBJECT-TYPE
			SYNTAX	INTEGER
			MAX-ACCESS	read-only
			STATUS	current
			::= { hmWanMbusBA 60 }

hmWanMbusBAValue1B		OBJECT-TYPE
			SYNTAX	INTEGER
			MAX-ACCESS	read-only
			STATUS	current
			::= { hmWanMbusBA 61 }

hmWanMbusBAVIF1C		OBJECT-TYPE
			SYNTAX	INTEGER
			MAX-ACCESS	read-only
			STATUS	current
			::= { hmWanMbusBA 62 }

hmWanMbusBAValue1C		OBJECT-TYPE
			SYNTAX	INTEGER
			MAX-ACCESS	read-only
			STATUS	current
			::= { hmWanMbusBA 63 }

hmWanMbusBAVIF1D		OBJECT-TYPE
			SYNTAX	INTEGER
			MAX-ACCESS	read-only
			STATUS	current
			::= { hmWanMbusBA 64 }

hmWanMbusBAValue1D		OBJECT-TYPE
			SYNTAX	INTEGER
			MAX-ACCESS	read-only
			STATUS	current
			::= { hmWanMbusBA 65 }

hmWanMbusBAVIF1E		OBJECT-TYPE
			SYNTAX	INTEGER
			MAX-ACCESS	read-only
			STATUS	current
			::= { hmWanMbusBA 66 }

hmWanMbusBAValue1E		OBJECT-TYPE
			SYNTAX	INTEGER
			MAX-ACCESS	read-only
			STATUS	current
			::= { hmWanMbusBA 67 }

hmWanMbusBAVIF1F		OBJECT-TYPE
			SYNTAX	INTEGER
			MAX-ACCESS	read-only
			STATUS	current
			::= { hmWanMbusBA 68 }

hmWanMbusBAValue1F		OBJECT-TYPE
			SYNTAX	INTEGER
			MAX-ACCESS	read-only
			STATUS	current
			::= { hmWanMbusBA 69 }

hmWanMbusBAVIF20		OBJECT-TYPE
			SYNTAX	INTEGER
			MAX-ACCESS	read-only
			STATUS	current
			::= { hmWanMbusBA 70 }

hmWanMbusBAValue20		OBJECT-TYPE
			SYNTAX	INTEGER
			MAX-ACCESS	read-only
			STATUS	current
			::= { hmWanMbusBA 71 }

hmWanMbusBAVIF21		OBJECT-TYPE
			SYNTAX	INTEGER
			MAX-ACCESS	read-only
			STATUS	current
			::= { hmWanMbusBA 72 }

hmWanMbusBAValue21		OBJECT-TYPE
			SYNTAX	INTEGER
			MAX-ACCESS	read-only
			STATUS	current
			::= { hmWanMbusBA 73 }

hmWanMbusBAVIF22		OBJECT-TYPE
			SYNTAX	INTEGER
			MAX-ACCESS	read-only
			STATUS	current
			::= { hmWanMbusBA 74 }

hmWanMbusBAValue22		OBJECT-TYPE
			SYNTAX	INTEGER
			MAX-ACCESS	read-only
			STATUS	current
			::= { hmWanMbusBA 75 }

hmWanMbusBAVIF23		OBJECT-TYPE
			SYNTAX	INTEGER
			MAX-ACCESS	read-only
			STATUS	current
			::= { hmWanMbusBA 76 }

hmWanMbusBAValue23		OBJECT-TYPE
			SYNTAX	INTEGER
			MAX-ACCESS	read-only
			STATUS	current
			::= { hmWanMbusBA 77 }

hmWanMbusBAVIF24		OBJECT-TYPE
			SYNTAX	INTEGER
			MAX-ACCESS	read-only
			STATUS	current
			::= { hmWanMbusBA 78 }

hmWanMbusBAValue24		OBJECT-TYPE
			SYNTAX	INTEGER
			MAX-ACCESS	read-only
			STATUS	current
			::= { hmWanMbusBA 79 }

hmWanMbusBAVIF25		OBJECT-TYPE
			SYNTAX	INTEGER
			MAX-ACCESS	read-only
			STATUS	current
			::= { hmWanMbusBA 80 }

hmWanMbusBAValue25		OBJECT-TYPE
			SYNTAX	INTEGER
			MAX-ACCESS	read-only
			STATUS	current
			::= { hmWanMbusBA 81 }

hmWanMbusBAVIF26		OBJECT-TYPE
			SYNTAX	INTEGER
			MAX-ACCESS	read-only
			STATUS	current
			::= { hmWanMbusBA 82 }

hmWanMbusBAValue26		OBJECT-TYPE
			SYNTAX	INTEGER
			MAX-ACCESS	read-only
			STATUS	current
			::= { hmWanMbusBA 83 }

hmWanMbusBAVIF27		OBJECT-TYPE
			SYNTAX	INTEGER
			MAX-ACCESS	read-only
			STATUS	current
			::= { hmWanMbusBA 84 }

hmWanMbusBAValue27		OBJECT-TYPE
			SYNTAX	INTEGER
			MAX-ACCESS	read-only
			STATUS	current
			::= { hmWanMbusBA 85 }

hmWanMbusBAVIF28		OBJECT-TYPE
			SYNTAX	INTEGER
			MAX-ACCESS	read-only
			STATUS	current
			::= { hmWanMbusBA 86 }

hmWanMbusBAValue28		OBJECT-TYPE
			SYNTAX	INTEGER
			MAX-ACCESS	read-only
			STATUS	current
			::= { hmWanMbusBA 87 }

hmWanMbusBAVIF29		OBJECT-TYPE
			SYNTAX	INTEGER
			MAX-ACCESS	read-only
			STATUS	current
			::= { hmWanMbusBA 88 }

hmWanMbusBAValue29		OBJECT-TYPE
			SYNTAX	INTEGER
			MAX-ACCESS	read-only
			STATUS	current
			::= { hmWanMbusBA 89 }

hmWanMbusBAVIF2A		OBJECT-TYPE
			SYNTAX	INTEGER
			MAX-ACCESS	read-only
			STATUS	current
			::= { hmWanMbusBA 90 }

hmWanMbusBAValue2A		OBJECT-TYPE
			SYNTAX	INTEGER
			MAX-ACCESS	read-only
			STATUS	current
			::= { hmWanMbusBA 91 }

hmWanMbusBAVIF2B		OBJECT-TYPE
			SYNTAX	INTEGER
			MAX-ACCESS	read-only
			STATUS	current
			::= { hmWanMbusBA 92 }

hmWanMbusBAValue2B		OBJECT-TYPE
			SYNTAX	INTEGER
			MAX-ACCESS	read-only
			STATUS	current
			::= { hmWanMbusBA 93 }

hmWanMbusBAVIF2C		OBJECT-TYPE
			SYNTAX	INTEGER
			MAX-ACCESS	read-only
			STATUS	current
			::= { hmWanMbusBA 94 }

hmWanMbusBAValue2C		OBJECT-TYPE
			SYNTAX	INTEGER
			MAX-ACCESS	read-only
			STATUS	current
			::= { hmWanMbusBA 95 }

hmWanMbusBAVIF2D		OBJECT-TYPE
			SYNTAX	INTEGER
			MAX-ACCESS	read-only
			STATUS	current
			::= { hmWanMbusBA 96 }

hmWanMbusBAValue2D		OBJECT-TYPE
			SYNTAX	INTEGER
			MAX-ACCESS	read-only
			STATUS	current
			::= { hmWanMbusBA 97 }

hmWanMbusBAVIF2E		OBJECT-TYPE
			SYNTAX	INTEGER
			MAX-ACCESS	read-only
			STATUS	current
			::= { hmWanMbusBA 98 }

hmWanMbusBAValue2E		OBJECT-TYPE
			SYNTAX	INTEGER
			MAX-ACCESS	read-only
			STATUS	current
			::= { hmWanMbusBA 99 }

hmWanMbusBAVIF2F		OBJECT-TYPE
			SYNTAX	INTEGER
			MAX-ACCESS	read-only
			STATUS	current
			::= { hmWanMbusBA 100 }

hmWanMbusBAValue2F		OBJECT-TYPE
			SYNTAX	INTEGER
			MAX-ACCESS	read-only
			STATUS	current
			::= { hmWanMbusBA 101 }

hmWanMbusBB			OBJECT IDENTIFIER ::= { hmWanMbus 187 }

hmWanMbusBBIdNumber		OBJECT-TYPE
			SYNTAX	Gauge32
			MAX-ACCESS	read-only
			STATUS	current
			::= { hmWanMbusBB 1 }

hmWanMbusBBManufacturer	OBJECT-TYPE
			SYNTAX	Gauge32
			MAX-ACCESS	read-only
			STATUS	current
			::= { hmWanMbusBB 2 }

hmWanMbusBBVersion		OBJECT-TYPE
			SYNTAX	Gauge32
			MAX-ACCESS	read-only
			STATUS	current
			::= { hmWanMbusBB 3 }

hmWanMbusBBMedium		OBJECT-TYPE
			SYNTAX	Gauge32
			MAX-ACCESS	read-only
			STATUS	current
			::= { hmWanMbusBB 4 }

hmWanMbusBBStatus		OBJECT-TYPE
			SYNTAX	Gauge32
			MAX-ACCESS	read-only
			STATUS	current
			::= { hmWanMbusBB 5 }

hmWanMbusBBVIF00		OBJECT-TYPE
			SYNTAX	INTEGER
			MAX-ACCESS	read-only
			STATUS	current
			::= { hmWanMbusBB 6 }

hmWanMbusBBValue00		OBJECT-TYPE
			SYNTAX	INTEGER
			MAX-ACCESS	read-only
			STATUS	current
			::= { hmWanMbusBB 7 }

hmWanMbusBBVIF01		OBJECT-TYPE
			SYNTAX	INTEGER
			MAX-ACCESS	read-only
			STATUS	current
			::= { hmWanMbusBB 8 }

hmWanMbusBBValue01		OBJECT-TYPE
			SYNTAX	INTEGER
			MAX-ACCESS	read-only
			STATUS	current
			::= { hmWanMbusBB 9 }

hmWanMbusBBVIF02		OBJECT-TYPE
			SYNTAX	INTEGER
			MAX-ACCESS	read-only
			STATUS	current
			::= { hmWanMbusBB 10 }

hmWanMbusBBValue02		OBJECT-TYPE
			SYNTAX	INTEGER
			MAX-ACCESS	read-only
			STATUS	current
			::= { hmWanMbusBB 11 }

hmWanMbusBBVIF03		OBJECT-TYPE
			SYNTAX	INTEGER
			MAX-ACCESS	read-only
			STATUS	current
			::= { hmWanMbusBB 12 }

hmWanMbusBBValue03		OBJECT-TYPE
			SYNTAX	INTEGER
			MAX-ACCESS	read-only
			STATUS	current
			::= { hmWanMbusBB 13 }

hmWanMbusBBVIF04		OBJECT-TYPE
			SYNTAX	INTEGER
			MAX-ACCESS	read-only
			STATUS	current
			::= { hmWanMbusBB 14 }

hmWanMbusBBValue04		OBJECT-TYPE
			SYNTAX	INTEGER
			MAX-ACCESS	read-only
			STATUS	current
			::= { hmWanMbusBB 15 }

hmWanMbusBBVIF05		OBJECT-TYPE
			SYNTAX	INTEGER
			MAX-ACCESS	read-only
			STATUS	current
			::= { hmWanMbusBB 16 }

hmWanMbusBBValue05		OBJECT-TYPE
			SYNTAX	INTEGER
			MAX-ACCESS	read-only
			STATUS	current
			::= { hmWanMbusBB 17 }

hmWanMbusBBVIF06		OBJECT-TYPE
			SYNTAX	INTEGER
			MAX-ACCESS	read-only
			STATUS	current
			::= { hmWanMbusBB 18 }

hmWanMbusBBValue06		OBJECT-TYPE
			SYNTAX	INTEGER
			MAX-ACCESS	read-only
			STATUS	current
			::= { hmWanMbusBB 19 }

hmWanMbusBBVIF07		OBJECT-TYPE
			SYNTAX	INTEGER
			MAX-ACCESS	read-only
			STATUS	current
			::= { hmWanMbusBB 20 }

hmWanMbusBBValue07		OBJECT-TYPE
			SYNTAX	INTEGER
			MAX-ACCESS	read-only
			STATUS	current
			::= { hmWanMbusBB 21 }

hmWanMbusBBVIF08		OBJECT-TYPE
			SYNTAX	INTEGER
			MAX-ACCESS	read-only
			STATUS	current
			::= { hmWanMbusBB 22 }

hmWanMbusBBValue08		OBJECT-TYPE
			SYNTAX	INTEGER
			MAX-ACCESS	read-only
			STATUS	current
			::= { hmWanMbusBB 23 }

hmWanMbusBBVIF09		OBJECT-TYPE
			SYNTAX	INTEGER
			MAX-ACCESS	read-only
			STATUS	current
			::= { hmWanMbusBB 24 }

hmWanMbusBBValue09		OBJECT-TYPE
			SYNTAX	INTEGER
			MAX-ACCESS	read-only
			STATUS	current
			::= { hmWanMbusBB 25 }

hmWanMbusBBVIF0A		OBJECT-TYPE
			SYNTAX	INTEGER
			MAX-ACCESS	read-only
			STATUS	current
			::= { hmWanMbusBB 26 }

hmWanMbusBBValue0A		OBJECT-TYPE
			SYNTAX	INTEGER
			MAX-ACCESS	read-only
			STATUS	current
			::= { hmWanMbusBB 27 }

hmWanMbusBBVIF0B		OBJECT-TYPE
			SYNTAX	INTEGER
			MAX-ACCESS	read-only
			STATUS	current
			::= { hmWanMbusBB 28 }

hmWanMbusBBValue0B		OBJECT-TYPE
			SYNTAX	INTEGER
			MAX-ACCESS	read-only
			STATUS	current
			::= { hmWanMbusBB 29 }

hmWanMbusBBVIF0C		OBJECT-TYPE
			SYNTAX	INTEGER
			MAX-ACCESS	read-only
			STATUS	current
			::= { hmWanMbusBB 30 }

hmWanMbusBBValue0C		OBJECT-TYPE
			SYNTAX	INTEGER
			MAX-ACCESS	read-only
			STATUS	current
			::= { hmWanMbusBB 31 }

hmWanMbusBBVIF0D		OBJECT-TYPE
			SYNTAX	INTEGER
			MAX-ACCESS	read-only
			STATUS	current
			::= { hmWanMbusBB 32 }

hmWanMbusBBValue0D		OBJECT-TYPE
			SYNTAX	INTEGER
			MAX-ACCESS	read-only
			STATUS	current
			::= { hmWanMbusBB 33 }

hmWanMbusBBVIF0E		OBJECT-TYPE
			SYNTAX	INTEGER
			MAX-ACCESS	read-only
			STATUS	current
			::= { hmWanMbusBB 34 }

hmWanMbusBBValue0E		OBJECT-TYPE
			SYNTAX	INTEGER
			MAX-ACCESS	read-only
			STATUS	current
			::= { hmWanMbusBB 35 }

hmWanMbusBBVIF0F		OBJECT-TYPE
			SYNTAX	INTEGER
			MAX-ACCESS	read-only
			STATUS	current
			::= { hmWanMbusBB 36 }

hmWanMbusBBValue0F		OBJECT-TYPE
			SYNTAX	INTEGER
			MAX-ACCESS	read-only
			STATUS	current
			::= { hmWanMbusBB 37 }

hmWanMbusBBVIF10		OBJECT-TYPE
			SYNTAX	INTEGER
			MAX-ACCESS	read-only
			STATUS	current
			::= { hmWanMbusBB 38 }

hmWanMbusBBValue10		OBJECT-TYPE
			SYNTAX	INTEGER
			MAX-ACCESS	read-only
			STATUS	current
			::= { hmWanMbusBB 39 }

hmWanMbusBBVIF11		OBJECT-TYPE
			SYNTAX	INTEGER
			MAX-ACCESS	read-only
			STATUS	current
			::= { hmWanMbusBB 40 }

hmWanMbusBBValue11		OBJECT-TYPE
			SYNTAX	INTEGER
			MAX-ACCESS	read-only
			STATUS	current
			::= { hmWanMbusBB 41 }

hmWanMbusBBVIF12		OBJECT-TYPE
			SYNTAX	INTEGER
			MAX-ACCESS	read-only
			STATUS	current
			::= { hmWanMbusBB 42 }

hmWanMbusBBValue12		OBJECT-TYPE
			SYNTAX	INTEGER
			MAX-ACCESS	read-only
			STATUS	current
			::= { hmWanMbusBB 43 }

hmWanMbusBBVIF13		OBJECT-TYPE
			SYNTAX	INTEGER
			MAX-ACCESS	read-only
			STATUS	current
			::= { hmWanMbusBB 44 }

hmWanMbusBBValue13		OBJECT-TYPE
			SYNTAX	INTEGER
			MAX-ACCESS	read-only
			STATUS	current
			::= { hmWanMbusBB 45 }

hmWanMbusBBVIF14		OBJECT-TYPE
			SYNTAX	INTEGER
			MAX-ACCESS	read-only
			STATUS	current
			::= { hmWanMbusBB 46 }

hmWanMbusBBValue14		OBJECT-TYPE
			SYNTAX	INTEGER
			MAX-ACCESS	read-only
			STATUS	current
			::= { hmWanMbusBB 47 }

hmWanMbusBBVIF15		OBJECT-TYPE
			SYNTAX	INTEGER
			MAX-ACCESS	read-only
			STATUS	current
			::= { hmWanMbusBB 48 }

hmWanMbusBBValue15		OBJECT-TYPE
			SYNTAX	INTEGER
			MAX-ACCESS	read-only
			STATUS	current
			::= { hmWanMbusBB 49 }

hmWanMbusBBVIF16		OBJECT-TYPE
			SYNTAX	INTEGER
			MAX-ACCESS	read-only
			STATUS	current
			::= { hmWanMbusBB 50 }

hmWanMbusBBValue16		OBJECT-TYPE
			SYNTAX	INTEGER
			MAX-ACCESS	read-only
			STATUS	current
			::= { hmWanMbusBB 51 }

hmWanMbusBBVIF17		OBJECT-TYPE
			SYNTAX	INTEGER
			MAX-ACCESS	read-only
			STATUS	current
			::= { hmWanMbusBB 52 }

hmWanMbusBBValue17		OBJECT-TYPE
			SYNTAX	INTEGER
			MAX-ACCESS	read-only
			STATUS	current
			::= { hmWanMbusBB 53 }

hmWanMbusBBVIF18		OBJECT-TYPE
			SYNTAX	INTEGER
			MAX-ACCESS	read-only
			STATUS	current
			::= { hmWanMbusBB 54 }

hmWanMbusBBValue18		OBJECT-TYPE
			SYNTAX	INTEGER
			MAX-ACCESS	read-only
			STATUS	current
			::= { hmWanMbusBB 55 }

hmWanMbusBBVIF19		OBJECT-TYPE
			SYNTAX	INTEGER
			MAX-ACCESS	read-only
			STATUS	current
			::= { hmWanMbusBB 56 }

hmWanMbusBBValue19		OBJECT-TYPE
			SYNTAX	INTEGER
			MAX-ACCESS	read-only
			STATUS	current
			::= { hmWanMbusBB 57 }

hmWanMbusBBVIF1A		OBJECT-TYPE
			SYNTAX	INTEGER
			MAX-ACCESS	read-only
			STATUS	current
			::= { hmWanMbusBB 58 }

hmWanMbusBBValue1A		OBJECT-TYPE
			SYNTAX	INTEGER
			MAX-ACCESS	read-only
			STATUS	current
			::= { hmWanMbusBB 59 }

hmWanMbusBBVIF1B		OBJECT-TYPE
			SYNTAX	INTEGER
			MAX-ACCESS	read-only
			STATUS	current
			::= { hmWanMbusBB 60 }

hmWanMbusBBValue1B		OBJECT-TYPE
			SYNTAX	INTEGER
			MAX-ACCESS	read-only
			STATUS	current
			::= { hmWanMbusBB 61 }

hmWanMbusBBVIF1C		OBJECT-TYPE
			SYNTAX	INTEGER
			MAX-ACCESS	read-only
			STATUS	current
			::= { hmWanMbusBB 62 }

hmWanMbusBBValue1C		OBJECT-TYPE
			SYNTAX	INTEGER
			MAX-ACCESS	read-only
			STATUS	current
			::= { hmWanMbusBB 63 }

hmWanMbusBBVIF1D		OBJECT-TYPE
			SYNTAX	INTEGER
			MAX-ACCESS	read-only
			STATUS	current
			::= { hmWanMbusBB 64 }

hmWanMbusBBValue1D		OBJECT-TYPE
			SYNTAX	INTEGER
			MAX-ACCESS	read-only
			STATUS	current
			::= { hmWanMbusBB 65 }

hmWanMbusBBVIF1E		OBJECT-TYPE
			SYNTAX	INTEGER
			MAX-ACCESS	read-only
			STATUS	current
			::= { hmWanMbusBB 66 }

hmWanMbusBBValue1E		OBJECT-TYPE
			SYNTAX	INTEGER
			MAX-ACCESS	read-only
			STATUS	current
			::= { hmWanMbusBB 67 }

hmWanMbusBBVIF1F		OBJECT-TYPE
			SYNTAX	INTEGER
			MAX-ACCESS	read-only
			STATUS	current
			::= { hmWanMbusBB 68 }

hmWanMbusBBValue1F		OBJECT-TYPE
			SYNTAX	INTEGER
			MAX-ACCESS	read-only
			STATUS	current
			::= { hmWanMbusBB 69 }

hmWanMbusBBVIF20		OBJECT-TYPE
			SYNTAX	INTEGER
			MAX-ACCESS	read-only
			STATUS	current
			::= { hmWanMbusBB 70 }

hmWanMbusBBValue20		OBJECT-TYPE
			SYNTAX	INTEGER
			MAX-ACCESS	read-only
			STATUS	current
			::= { hmWanMbusBB 71 }

hmWanMbusBBVIF21		OBJECT-TYPE
			SYNTAX	INTEGER
			MAX-ACCESS	read-only
			STATUS	current
			::= { hmWanMbusBB 72 }

hmWanMbusBBValue21		OBJECT-TYPE
			SYNTAX	INTEGER
			MAX-ACCESS	read-only
			STATUS	current
			::= { hmWanMbusBB 73 }

hmWanMbusBBVIF22		OBJECT-TYPE
			SYNTAX	INTEGER
			MAX-ACCESS	read-only
			STATUS	current
			::= { hmWanMbusBB 74 }

hmWanMbusBBValue22		OBJECT-TYPE
			SYNTAX	INTEGER
			MAX-ACCESS	read-only
			STATUS	current
			::= { hmWanMbusBB 75 }

hmWanMbusBBVIF23		OBJECT-TYPE
			SYNTAX	INTEGER
			MAX-ACCESS	read-only
			STATUS	current
			::= { hmWanMbusBB 76 }

hmWanMbusBBValue23		OBJECT-TYPE
			SYNTAX	INTEGER
			MAX-ACCESS	read-only
			STATUS	current
			::= { hmWanMbusBB 77 }

hmWanMbusBBVIF24		OBJECT-TYPE
			SYNTAX	INTEGER
			MAX-ACCESS	read-only
			STATUS	current
			::= { hmWanMbusBB 78 }

hmWanMbusBBValue24		OBJECT-TYPE
			SYNTAX	INTEGER
			MAX-ACCESS	read-only
			STATUS	current
			::= { hmWanMbusBB 79 }

hmWanMbusBBVIF25		OBJECT-TYPE
			SYNTAX	INTEGER
			MAX-ACCESS	read-only
			STATUS	current
			::= { hmWanMbusBB 80 }

hmWanMbusBBValue25		OBJECT-TYPE
			SYNTAX	INTEGER
			MAX-ACCESS	read-only
			STATUS	current
			::= { hmWanMbusBB 81 }

hmWanMbusBBVIF26		OBJECT-TYPE
			SYNTAX	INTEGER
			MAX-ACCESS	read-only
			STATUS	current
			::= { hmWanMbusBB 82 }

hmWanMbusBBValue26		OBJECT-TYPE
			SYNTAX	INTEGER
			MAX-ACCESS	read-only
			STATUS	current
			::= { hmWanMbusBB 83 }

hmWanMbusBBVIF27		OBJECT-TYPE
			SYNTAX	INTEGER
			MAX-ACCESS	read-only
			STATUS	current
			::= { hmWanMbusBB 84 }

hmWanMbusBBValue27		OBJECT-TYPE
			SYNTAX	INTEGER
			MAX-ACCESS	read-only
			STATUS	current
			::= { hmWanMbusBB 85 }

hmWanMbusBBVIF28		OBJECT-TYPE
			SYNTAX	INTEGER
			MAX-ACCESS	read-only
			STATUS	current
			::= { hmWanMbusBB 86 }

hmWanMbusBBValue28		OBJECT-TYPE
			SYNTAX	INTEGER
			MAX-ACCESS	read-only
			STATUS	current
			::= { hmWanMbusBB 87 }

hmWanMbusBBVIF29		OBJECT-TYPE
			SYNTAX	INTEGER
			MAX-ACCESS	read-only
			STATUS	current
			::= { hmWanMbusBB 88 }

hmWanMbusBBValue29		OBJECT-TYPE
			SYNTAX	INTEGER
			MAX-ACCESS	read-only
			STATUS	current
			::= { hmWanMbusBB 89 }

hmWanMbusBBVIF2A		OBJECT-TYPE
			SYNTAX	INTEGER
			MAX-ACCESS	read-only
			STATUS	current
			::= { hmWanMbusBB 90 }

hmWanMbusBBValue2A		OBJECT-TYPE
			SYNTAX	INTEGER
			MAX-ACCESS	read-only
			STATUS	current
			::= { hmWanMbusBB 91 }

hmWanMbusBBVIF2B		OBJECT-TYPE
			SYNTAX	INTEGER
			MAX-ACCESS	read-only
			STATUS	current
			::= { hmWanMbusBB 92 }

hmWanMbusBBValue2B		OBJECT-TYPE
			SYNTAX	INTEGER
			MAX-ACCESS	read-only
			STATUS	current
			::= { hmWanMbusBB 93 }

hmWanMbusBBVIF2C		OBJECT-TYPE
			SYNTAX	INTEGER
			MAX-ACCESS	read-only
			STATUS	current
			::= { hmWanMbusBB 94 }

hmWanMbusBBValue2C		OBJECT-TYPE
			SYNTAX	INTEGER
			MAX-ACCESS	read-only
			STATUS	current
			::= { hmWanMbusBB 95 }

hmWanMbusBBVIF2D		OBJECT-TYPE
			SYNTAX	INTEGER
			MAX-ACCESS	read-only
			STATUS	current
			::= { hmWanMbusBB 96 }

hmWanMbusBBValue2D		OBJECT-TYPE
			SYNTAX	INTEGER
			MAX-ACCESS	read-only
			STATUS	current
			::= { hmWanMbusBB 97 }

hmWanMbusBBVIF2E		OBJECT-TYPE
			SYNTAX	INTEGER
			MAX-ACCESS	read-only
			STATUS	current
			::= { hmWanMbusBB 98 }

hmWanMbusBBValue2E		OBJECT-TYPE
			SYNTAX	INTEGER
			MAX-ACCESS	read-only
			STATUS	current
			::= { hmWanMbusBB 99 }

hmWanMbusBBVIF2F		OBJECT-TYPE
			SYNTAX	INTEGER
			MAX-ACCESS	read-only
			STATUS	current
			::= { hmWanMbusBB 100 }

hmWanMbusBBValue2F		OBJECT-TYPE
			SYNTAX	INTEGER
			MAX-ACCESS	read-only
			STATUS	current
			::= { hmWanMbusBB 101 }

hmWanMbusBC			OBJECT IDENTIFIER ::= { hmWanMbus 188 }

hmWanMbusBCIdNumber		OBJECT-TYPE
			SYNTAX	Gauge32
			MAX-ACCESS	read-only
			STATUS	current
			::= { hmWanMbusBC 1 }

hmWanMbusBCManufacturer	OBJECT-TYPE
			SYNTAX	Gauge32
			MAX-ACCESS	read-only
			STATUS	current
			::= { hmWanMbusBC 2 }

hmWanMbusBCVersion		OBJECT-TYPE
			SYNTAX	Gauge32
			MAX-ACCESS	read-only
			STATUS	current
			::= { hmWanMbusBC 3 }

hmWanMbusBCMedium		OBJECT-TYPE
			SYNTAX	Gauge32
			MAX-ACCESS	read-only
			STATUS	current
			::= { hmWanMbusBC 4 }

hmWanMbusBCStatus		OBJECT-TYPE
			SYNTAX	Gauge32
			MAX-ACCESS	read-only
			STATUS	current
			::= { hmWanMbusBC 5 }

hmWanMbusBCVIF00		OBJECT-TYPE
			SYNTAX	INTEGER
			MAX-ACCESS	read-only
			STATUS	current
			::= { hmWanMbusBC 6 }

hmWanMbusBCValue00		OBJECT-TYPE
			SYNTAX	INTEGER
			MAX-ACCESS	read-only
			STATUS	current
			::= { hmWanMbusBC 7 }

hmWanMbusBCVIF01		OBJECT-TYPE
			SYNTAX	INTEGER
			MAX-ACCESS	read-only
			STATUS	current
			::= { hmWanMbusBC 8 }

hmWanMbusBCValue01		OBJECT-TYPE
			SYNTAX	INTEGER
			MAX-ACCESS	read-only
			STATUS	current
			::= { hmWanMbusBC 9 }

hmWanMbusBCVIF02		OBJECT-TYPE
			SYNTAX	INTEGER
			MAX-ACCESS	read-only
			STATUS	current
			::= { hmWanMbusBC 10 }

hmWanMbusBCValue02		OBJECT-TYPE
			SYNTAX	INTEGER
			MAX-ACCESS	read-only
			STATUS	current
			::= { hmWanMbusBC 11 }

hmWanMbusBCVIF03		OBJECT-TYPE
			SYNTAX	INTEGER
			MAX-ACCESS	read-only
			STATUS	current
			::= { hmWanMbusBC 12 }

hmWanMbusBCValue03		OBJECT-TYPE
			SYNTAX	INTEGER
			MAX-ACCESS	read-only
			STATUS	current
			::= { hmWanMbusBC 13 }

hmWanMbusBCVIF04		OBJECT-TYPE
			SYNTAX	INTEGER
			MAX-ACCESS	read-only
			STATUS	current
			::= { hmWanMbusBC 14 }

hmWanMbusBCValue04		OBJECT-TYPE
			SYNTAX	INTEGER
			MAX-ACCESS	read-only
			STATUS	current
			::= { hmWanMbusBC 15 }

hmWanMbusBCVIF05		OBJECT-TYPE
			SYNTAX	INTEGER
			MAX-ACCESS	read-only
			STATUS	current
			::= { hmWanMbusBC 16 }

hmWanMbusBCValue05		OBJECT-TYPE
			SYNTAX	INTEGER
			MAX-ACCESS	read-only
			STATUS	current
			::= { hmWanMbusBC 17 }

hmWanMbusBCVIF06		OBJECT-TYPE
			SYNTAX	INTEGER
			MAX-ACCESS	read-only
			STATUS	current
			::= { hmWanMbusBC 18 }

hmWanMbusBCValue06		OBJECT-TYPE
			SYNTAX	INTEGER
			MAX-ACCESS	read-only
			STATUS	current
			::= { hmWanMbusBC 19 }

hmWanMbusBCVIF07		OBJECT-TYPE
			SYNTAX	INTEGER
			MAX-ACCESS	read-only
			STATUS	current
			::= { hmWanMbusBC 20 }

hmWanMbusBCValue07		OBJECT-TYPE
			SYNTAX	INTEGER
			MAX-ACCESS	read-only
			STATUS	current
			::= { hmWanMbusBC 21 }

hmWanMbusBCVIF08		OBJECT-TYPE
			SYNTAX	INTEGER
			MAX-ACCESS	read-only
			STATUS	current
			::= { hmWanMbusBC 22 }

hmWanMbusBCValue08		OBJECT-TYPE
			SYNTAX	INTEGER
			MAX-ACCESS	read-only
			STATUS	current
			::= { hmWanMbusBC 23 }

hmWanMbusBCVIF09		OBJECT-TYPE
			SYNTAX	INTEGER
			MAX-ACCESS	read-only
			STATUS	current
			::= { hmWanMbusBC 24 }

hmWanMbusBCValue09		OBJECT-TYPE
			SYNTAX	INTEGER
			MAX-ACCESS	read-only
			STATUS	current
			::= { hmWanMbusBC 25 }

hmWanMbusBCVIF0A		OBJECT-TYPE
			SYNTAX	INTEGER
			MAX-ACCESS	read-only
			STATUS	current
			::= { hmWanMbusBC 26 }

hmWanMbusBCValue0A		OBJECT-TYPE
			SYNTAX	INTEGER
			MAX-ACCESS	read-only
			STATUS	current
			::= { hmWanMbusBC 27 }

hmWanMbusBCVIF0B		OBJECT-TYPE
			SYNTAX	INTEGER
			MAX-ACCESS	read-only
			STATUS	current
			::= { hmWanMbusBC 28 }

hmWanMbusBCValue0B		OBJECT-TYPE
			SYNTAX	INTEGER
			MAX-ACCESS	read-only
			STATUS	current
			::= { hmWanMbusBC 29 }

hmWanMbusBCVIF0C		OBJECT-TYPE
			SYNTAX	INTEGER
			MAX-ACCESS	read-only
			STATUS	current
			::= { hmWanMbusBC 30 }

hmWanMbusBCValue0C		OBJECT-TYPE
			SYNTAX	INTEGER
			MAX-ACCESS	read-only
			STATUS	current
			::= { hmWanMbusBC 31 }

hmWanMbusBCVIF0D		OBJECT-TYPE
			SYNTAX	INTEGER
			MAX-ACCESS	read-only
			STATUS	current
			::= { hmWanMbusBC 32 }

hmWanMbusBCValue0D		OBJECT-TYPE
			SYNTAX	INTEGER
			MAX-ACCESS	read-only
			STATUS	current
			::= { hmWanMbusBC 33 }

hmWanMbusBCVIF0E		OBJECT-TYPE
			SYNTAX	INTEGER
			MAX-ACCESS	read-only
			STATUS	current
			::= { hmWanMbusBC 34 }

hmWanMbusBCValue0E		OBJECT-TYPE
			SYNTAX	INTEGER
			MAX-ACCESS	read-only
			STATUS	current
			::= { hmWanMbusBC 35 }

hmWanMbusBCVIF0F		OBJECT-TYPE
			SYNTAX	INTEGER
			MAX-ACCESS	read-only
			STATUS	current
			::= { hmWanMbusBC 36 }

hmWanMbusBCValue0F		OBJECT-TYPE
			SYNTAX	INTEGER
			MAX-ACCESS	read-only
			STATUS	current
			::= { hmWanMbusBC 37 }

hmWanMbusBCVIF10		OBJECT-TYPE
			SYNTAX	INTEGER
			MAX-ACCESS	read-only
			STATUS	current
			::= { hmWanMbusBC 38 }

hmWanMbusBCValue10		OBJECT-TYPE
			SYNTAX	INTEGER
			MAX-ACCESS	read-only
			STATUS	current
			::= { hmWanMbusBC 39 }

hmWanMbusBCVIF11		OBJECT-TYPE
			SYNTAX	INTEGER
			MAX-ACCESS	read-only
			STATUS	current
			::= { hmWanMbusBC 40 }

hmWanMbusBCValue11		OBJECT-TYPE
			SYNTAX	INTEGER
			MAX-ACCESS	read-only
			STATUS	current
			::= { hmWanMbusBC 41 }

hmWanMbusBCVIF12		OBJECT-TYPE
			SYNTAX	INTEGER
			MAX-ACCESS	read-only
			STATUS	current
			::= { hmWanMbusBC 42 }

hmWanMbusBCValue12		OBJECT-TYPE
			SYNTAX	INTEGER
			MAX-ACCESS	read-only
			STATUS	current
			::= { hmWanMbusBC 43 }

hmWanMbusBCVIF13		OBJECT-TYPE
			SYNTAX	INTEGER
			MAX-ACCESS	read-only
			STATUS	current
			::= { hmWanMbusBC 44 }

hmWanMbusBCValue13		OBJECT-TYPE
			SYNTAX	INTEGER
			MAX-ACCESS	read-only
			STATUS	current
			::= { hmWanMbusBC 45 }

hmWanMbusBCVIF14		OBJECT-TYPE
			SYNTAX	INTEGER
			MAX-ACCESS	read-only
			STATUS	current
			::= { hmWanMbusBC 46 }

hmWanMbusBCValue14		OBJECT-TYPE
			SYNTAX	INTEGER
			MAX-ACCESS	read-only
			STATUS	current
			::= { hmWanMbusBC 47 }

hmWanMbusBCVIF15		OBJECT-TYPE
			SYNTAX	INTEGER
			MAX-ACCESS	read-only
			STATUS	current
			::= { hmWanMbusBC 48 }

hmWanMbusBCValue15		OBJECT-TYPE
			SYNTAX	INTEGER
			MAX-ACCESS	read-only
			STATUS	current
			::= { hmWanMbusBC 49 }

hmWanMbusBCVIF16		OBJECT-TYPE
			SYNTAX	INTEGER
			MAX-ACCESS	read-only
			STATUS	current
			::= { hmWanMbusBC 50 }

hmWanMbusBCValue16		OBJECT-TYPE
			SYNTAX	INTEGER
			MAX-ACCESS	read-only
			STATUS	current
			::= { hmWanMbusBC 51 }

hmWanMbusBCVIF17		OBJECT-TYPE
			SYNTAX	INTEGER
			MAX-ACCESS	read-only
			STATUS	current
			::= { hmWanMbusBC 52 }

hmWanMbusBCValue17		OBJECT-TYPE
			SYNTAX	INTEGER
			MAX-ACCESS	read-only
			STATUS	current
			::= { hmWanMbusBC 53 }

hmWanMbusBCVIF18		OBJECT-TYPE
			SYNTAX	INTEGER
			MAX-ACCESS	read-only
			STATUS	current
			::= { hmWanMbusBC 54 }

hmWanMbusBCValue18		OBJECT-TYPE
			SYNTAX	INTEGER
			MAX-ACCESS	read-only
			STATUS	current
			::= { hmWanMbusBC 55 }

hmWanMbusBCVIF19		OBJECT-TYPE
			SYNTAX	INTEGER
			MAX-ACCESS	read-only
			STATUS	current
			::= { hmWanMbusBC 56 }

hmWanMbusBCValue19		OBJECT-TYPE
			SYNTAX	INTEGER
			MAX-ACCESS	read-only
			STATUS	current
			::= { hmWanMbusBC 57 }

hmWanMbusBCVIF1A		OBJECT-TYPE
			SYNTAX	INTEGER
			MAX-ACCESS	read-only
			STATUS	current
			::= { hmWanMbusBC 58 }

hmWanMbusBCValue1A		OBJECT-TYPE
			SYNTAX	INTEGER
			MAX-ACCESS	read-only
			STATUS	current
			::= { hmWanMbusBC 59 }

hmWanMbusBCVIF1B		OBJECT-TYPE
			SYNTAX	INTEGER
			MAX-ACCESS	read-only
			STATUS	current
			::= { hmWanMbusBC 60 }

hmWanMbusBCValue1B		OBJECT-TYPE
			SYNTAX	INTEGER
			MAX-ACCESS	read-only
			STATUS	current
			::= { hmWanMbusBC 61 }

hmWanMbusBCVIF1C		OBJECT-TYPE
			SYNTAX	INTEGER
			MAX-ACCESS	read-only
			STATUS	current
			::= { hmWanMbusBC 62 }

hmWanMbusBCValue1C		OBJECT-TYPE
			SYNTAX	INTEGER
			MAX-ACCESS	read-only
			STATUS	current
			::= { hmWanMbusBC 63 }

hmWanMbusBCVIF1D		OBJECT-TYPE
			SYNTAX	INTEGER
			MAX-ACCESS	read-only
			STATUS	current
			::= { hmWanMbusBC 64 }

hmWanMbusBCValue1D		OBJECT-TYPE
			SYNTAX	INTEGER
			MAX-ACCESS	read-only
			STATUS	current
			::= { hmWanMbusBC 65 }

hmWanMbusBCVIF1E		OBJECT-TYPE
			SYNTAX	INTEGER
			MAX-ACCESS	read-only
			STATUS	current
			::= { hmWanMbusBC 66 }

hmWanMbusBCValue1E		OBJECT-TYPE
			SYNTAX	INTEGER
			MAX-ACCESS	read-only
			STATUS	current
			::= { hmWanMbusBC 67 }

hmWanMbusBCVIF1F		OBJECT-TYPE
			SYNTAX	INTEGER
			MAX-ACCESS	read-only
			STATUS	current
			::= { hmWanMbusBC 68 }

hmWanMbusBCValue1F		OBJECT-TYPE
			SYNTAX	INTEGER
			MAX-ACCESS	read-only
			STATUS	current
			::= { hmWanMbusBC 69 }

hmWanMbusBCVIF20		OBJECT-TYPE
			SYNTAX	INTEGER
			MAX-ACCESS	read-only
			STATUS	current
			::= { hmWanMbusBC 70 }

hmWanMbusBCValue20		OBJECT-TYPE
			SYNTAX	INTEGER
			MAX-ACCESS	read-only
			STATUS	current
			::= { hmWanMbusBC 71 }

hmWanMbusBCVIF21		OBJECT-TYPE
			SYNTAX	INTEGER
			MAX-ACCESS	read-only
			STATUS	current
			::= { hmWanMbusBC 72 }

hmWanMbusBCValue21		OBJECT-TYPE
			SYNTAX	INTEGER
			MAX-ACCESS	read-only
			STATUS	current
			::= { hmWanMbusBC 73 }

hmWanMbusBCVIF22		OBJECT-TYPE
			SYNTAX	INTEGER
			MAX-ACCESS	read-only
			STATUS	current
			::= { hmWanMbusBC 74 }

hmWanMbusBCValue22		OBJECT-TYPE
			SYNTAX	INTEGER
			MAX-ACCESS	read-only
			STATUS	current
			::= { hmWanMbusBC 75 }

hmWanMbusBCVIF23		OBJECT-TYPE
			SYNTAX	INTEGER
			MAX-ACCESS	read-only
			STATUS	current
			::= { hmWanMbusBC 76 }

hmWanMbusBCValue23		OBJECT-TYPE
			SYNTAX	INTEGER
			MAX-ACCESS	read-only
			STATUS	current
			::= { hmWanMbusBC 77 }

hmWanMbusBCVIF24		OBJECT-TYPE
			SYNTAX	INTEGER
			MAX-ACCESS	read-only
			STATUS	current
			::= { hmWanMbusBC 78 }

hmWanMbusBCValue24		OBJECT-TYPE
			SYNTAX	INTEGER
			MAX-ACCESS	read-only
			STATUS	current
			::= { hmWanMbusBC 79 }

hmWanMbusBCVIF25		OBJECT-TYPE
			SYNTAX	INTEGER
			MAX-ACCESS	read-only
			STATUS	current
			::= { hmWanMbusBC 80 }

hmWanMbusBCValue25		OBJECT-TYPE
			SYNTAX	INTEGER
			MAX-ACCESS	read-only
			STATUS	current
			::= { hmWanMbusBC 81 }

hmWanMbusBCVIF26		OBJECT-TYPE
			SYNTAX	INTEGER
			MAX-ACCESS	read-only
			STATUS	current
			::= { hmWanMbusBC 82 }

hmWanMbusBCValue26		OBJECT-TYPE
			SYNTAX	INTEGER
			MAX-ACCESS	read-only
			STATUS	current
			::= { hmWanMbusBC 83 }

hmWanMbusBCVIF27		OBJECT-TYPE
			SYNTAX	INTEGER
			MAX-ACCESS	read-only
			STATUS	current
			::= { hmWanMbusBC 84 }

hmWanMbusBCValue27		OBJECT-TYPE
			SYNTAX	INTEGER
			MAX-ACCESS	read-only
			STATUS	current
			::= { hmWanMbusBC 85 }

hmWanMbusBCVIF28		OBJECT-TYPE
			SYNTAX	INTEGER
			MAX-ACCESS	read-only
			STATUS	current
			::= { hmWanMbusBC 86 }

hmWanMbusBCValue28		OBJECT-TYPE
			SYNTAX	INTEGER
			MAX-ACCESS	read-only
			STATUS	current
			::= { hmWanMbusBC 87 }

hmWanMbusBCVIF29		OBJECT-TYPE
			SYNTAX	INTEGER
			MAX-ACCESS	read-only
			STATUS	current
			::= { hmWanMbusBC 88 }

hmWanMbusBCValue29		OBJECT-TYPE
			SYNTAX	INTEGER
			MAX-ACCESS	read-only
			STATUS	current
			::= { hmWanMbusBC 89 }

hmWanMbusBCVIF2A		OBJECT-TYPE
			SYNTAX	INTEGER
			MAX-ACCESS	read-only
			STATUS	current
			::= { hmWanMbusBC 90 }

hmWanMbusBCValue2A		OBJECT-TYPE
			SYNTAX	INTEGER
			MAX-ACCESS	read-only
			STATUS	current
			::= { hmWanMbusBC 91 }

hmWanMbusBCVIF2B		OBJECT-TYPE
			SYNTAX	INTEGER
			MAX-ACCESS	read-only
			STATUS	current
			::= { hmWanMbusBC 92 }

hmWanMbusBCValue2B		OBJECT-TYPE
			SYNTAX	INTEGER
			MAX-ACCESS	read-only
			STATUS	current
			::= { hmWanMbusBC 93 }

hmWanMbusBCVIF2C		OBJECT-TYPE
			SYNTAX	INTEGER
			MAX-ACCESS	read-only
			STATUS	current
			::= { hmWanMbusBC 94 }

hmWanMbusBCValue2C		OBJECT-TYPE
			SYNTAX	INTEGER
			MAX-ACCESS	read-only
			STATUS	current
			::= { hmWanMbusBC 95 }

hmWanMbusBCVIF2D		OBJECT-TYPE
			SYNTAX	INTEGER
			MAX-ACCESS	read-only
			STATUS	current
			::= { hmWanMbusBC 96 }

hmWanMbusBCValue2D		OBJECT-TYPE
			SYNTAX	INTEGER
			MAX-ACCESS	read-only
			STATUS	current
			::= { hmWanMbusBC 97 }

hmWanMbusBCVIF2E		OBJECT-TYPE
			SYNTAX	INTEGER
			MAX-ACCESS	read-only
			STATUS	current
			::= { hmWanMbusBC 98 }

hmWanMbusBCValue2E		OBJECT-TYPE
			SYNTAX	INTEGER
			MAX-ACCESS	read-only
			STATUS	current
			::= { hmWanMbusBC 99 }

hmWanMbusBCVIF2F		OBJECT-TYPE
			SYNTAX	INTEGER
			MAX-ACCESS	read-only
			STATUS	current
			::= { hmWanMbusBC 100 }

hmWanMbusBCValue2F		OBJECT-TYPE
			SYNTAX	INTEGER
			MAX-ACCESS	read-only
			STATUS	current
			::= { hmWanMbusBC 101 }

hmWanMbusBD			OBJECT IDENTIFIER ::= { hmWanMbus 189 }

hmWanMbusBDIdNumber		OBJECT-TYPE
			SYNTAX	Gauge32
			MAX-ACCESS	read-only
			STATUS	current
			::= { hmWanMbusBD 1 }

hmWanMbusBDManufacturer	OBJECT-TYPE
			SYNTAX	Gauge32
			MAX-ACCESS	read-only
			STATUS	current
			::= { hmWanMbusBD 2 }

hmWanMbusBDVersion		OBJECT-TYPE
			SYNTAX	Gauge32
			MAX-ACCESS	read-only
			STATUS	current
			::= { hmWanMbusBD 3 }

hmWanMbusBDMedium		OBJECT-TYPE
			SYNTAX	Gauge32
			MAX-ACCESS	read-only
			STATUS	current
			::= { hmWanMbusBD 4 }

hmWanMbusBDStatus		OBJECT-TYPE
			SYNTAX	Gauge32
			MAX-ACCESS	read-only
			STATUS	current
			::= { hmWanMbusBD 5 }

hmWanMbusBDVIF00		OBJECT-TYPE
			SYNTAX	INTEGER
			MAX-ACCESS	read-only
			STATUS	current
			::= { hmWanMbusBD 6 }

hmWanMbusBDValue00		OBJECT-TYPE
			SYNTAX	INTEGER
			MAX-ACCESS	read-only
			STATUS	current
			::= { hmWanMbusBD 7 }

hmWanMbusBDVIF01		OBJECT-TYPE
			SYNTAX	INTEGER
			MAX-ACCESS	read-only
			STATUS	current
			::= { hmWanMbusBD 8 }

hmWanMbusBDValue01		OBJECT-TYPE
			SYNTAX	INTEGER
			MAX-ACCESS	read-only
			STATUS	current
			::= { hmWanMbusBD 9 }

hmWanMbusBDVIF02		OBJECT-TYPE
			SYNTAX	INTEGER
			MAX-ACCESS	read-only
			STATUS	current
			::= { hmWanMbusBD 10 }

hmWanMbusBDValue02		OBJECT-TYPE
			SYNTAX	INTEGER
			MAX-ACCESS	read-only
			STATUS	current
			::= { hmWanMbusBD 11 }

hmWanMbusBDVIF03		OBJECT-TYPE
			SYNTAX	INTEGER
			MAX-ACCESS	read-only
			STATUS	current
			::= { hmWanMbusBD 12 }

hmWanMbusBDValue03		OBJECT-TYPE
			SYNTAX	INTEGER
			MAX-ACCESS	read-only
			STATUS	current
			::= { hmWanMbusBD 13 }

hmWanMbusBDVIF04		OBJECT-TYPE
			SYNTAX	INTEGER
			MAX-ACCESS	read-only
			STATUS	current
			::= { hmWanMbusBD 14 }

hmWanMbusBDValue04		OBJECT-TYPE
			SYNTAX	INTEGER
			MAX-ACCESS	read-only
			STATUS	current
			::= { hmWanMbusBD 15 }

hmWanMbusBDVIF05		OBJECT-TYPE
			SYNTAX	INTEGER
			MAX-ACCESS	read-only
			STATUS	current
			::= { hmWanMbusBD 16 }

hmWanMbusBDValue05		OBJECT-TYPE
			SYNTAX	INTEGER
			MAX-ACCESS	read-only
			STATUS	current
			::= { hmWanMbusBD 17 }

hmWanMbusBDVIF06		OBJECT-TYPE
			SYNTAX	INTEGER
			MAX-ACCESS	read-only
			STATUS	current
			::= { hmWanMbusBD 18 }

hmWanMbusBDValue06		OBJECT-TYPE
			SYNTAX	INTEGER
			MAX-ACCESS	read-only
			STATUS	current
			::= { hmWanMbusBD 19 }

hmWanMbusBDVIF07		OBJECT-TYPE
			SYNTAX	INTEGER
			MAX-ACCESS	read-only
			STATUS	current
			::= { hmWanMbusBD 20 }

hmWanMbusBDValue07		OBJECT-TYPE
			SYNTAX	INTEGER
			MAX-ACCESS	read-only
			STATUS	current
			::= { hmWanMbusBD 21 }

hmWanMbusBDVIF08		OBJECT-TYPE
			SYNTAX	INTEGER
			MAX-ACCESS	read-only
			STATUS	current
			::= { hmWanMbusBD 22 }

hmWanMbusBDValue08		OBJECT-TYPE
			SYNTAX	INTEGER
			MAX-ACCESS	read-only
			STATUS	current
			::= { hmWanMbusBD 23 }

hmWanMbusBDVIF09		OBJECT-TYPE
			SYNTAX	INTEGER
			MAX-ACCESS	read-only
			STATUS	current
			::= { hmWanMbusBD 24 }

hmWanMbusBDValue09		OBJECT-TYPE
			SYNTAX	INTEGER
			MAX-ACCESS	read-only
			STATUS	current
			::= { hmWanMbusBD 25 }

hmWanMbusBDVIF0A		OBJECT-TYPE
			SYNTAX	INTEGER
			MAX-ACCESS	read-only
			STATUS	current
			::= { hmWanMbusBD 26 }

hmWanMbusBDValue0A		OBJECT-TYPE
			SYNTAX	INTEGER
			MAX-ACCESS	read-only
			STATUS	current
			::= { hmWanMbusBD 27 }

hmWanMbusBDVIF0B		OBJECT-TYPE
			SYNTAX	INTEGER
			MAX-ACCESS	read-only
			STATUS	current
			::= { hmWanMbusBD 28 }

hmWanMbusBDValue0B		OBJECT-TYPE
			SYNTAX	INTEGER
			MAX-ACCESS	read-only
			STATUS	current
			::= { hmWanMbusBD 29 }

hmWanMbusBDVIF0C		OBJECT-TYPE
			SYNTAX	INTEGER
			MAX-ACCESS	read-only
			STATUS	current
			::= { hmWanMbusBD 30 }

hmWanMbusBDValue0C		OBJECT-TYPE
			SYNTAX	INTEGER
			MAX-ACCESS	read-only
			STATUS	current
			::= { hmWanMbusBD 31 }

hmWanMbusBDVIF0D		OBJECT-TYPE
			SYNTAX	INTEGER
			MAX-ACCESS	read-only
			STATUS	current
			::= { hmWanMbusBD 32 }

hmWanMbusBDValue0D		OBJECT-TYPE
			SYNTAX	INTEGER
			MAX-ACCESS	read-only
			STATUS	current
			::= { hmWanMbusBD 33 }

hmWanMbusBDVIF0E		OBJECT-TYPE
			SYNTAX	INTEGER
			MAX-ACCESS	read-only
			STATUS	current
			::= { hmWanMbusBD 34 }

hmWanMbusBDValue0E		OBJECT-TYPE
			SYNTAX	INTEGER
			MAX-ACCESS	read-only
			STATUS	current
			::= { hmWanMbusBD 35 }

hmWanMbusBDVIF0F		OBJECT-TYPE
			SYNTAX	INTEGER
			MAX-ACCESS	read-only
			STATUS	current
			::= { hmWanMbusBD 36 }

hmWanMbusBDValue0F		OBJECT-TYPE
			SYNTAX	INTEGER
			MAX-ACCESS	read-only
			STATUS	current
			::= { hmWanMbusBD 37 }

hmWanMbusBDVIF10		OBJECT-TYPE
			SYNTAX	INTEGER
			MAX-ACCESS	read-only
			STATUS	current
			::= { hmWanMbusBD 38 }

hmWanMbusBDValue10		OBJECT-TYPE
			SYNTAX	INTEGER
			MAX-ACCESS	read-only
			STATUS	current
			::= { hmWanMbusBD 39 }

hmWanMbusBDVIF11		OBJECT-TYPE
			SYNTAX	INTEGER
			MAX-ACCESS	read-only
			STATUS	current
			::= { hmWanMbusBD 40 }

hmWanMbusBDValue11		OBJECT-TYPE
			SYNTAX	INTEGER
			MAX-ACCESS	read-only
			STATUS	current
			::= { hmWanMbusBD 41 }

hmWanMbusBDVIF12		OBJECT-TYPE
			SYNTAX	INTEGER
			MAX-ACCESS	read-only
			STATUS	current
			::= { hmWanMbusBD 42 }

hmWanMbusBDValue12		OBJECT-TYPE
			SYNTAX	INTEGER
			MAX-ACCESS	read-only
			STATUS	current
			::= { hmWanMbusBD 43 }

hmWanMbusBDVIF13		OBJECT-TYPE
			SYNTAX	INTEGER
			MAX-ACCESS	read-only
			STATUS	current
			::= { hmWanMbusBD 44 }

hmWanMbusBDValue13		OBJECT-TYPE
			SYNTAX	INTEGER
			MAX-ACCESS	read-only
			STATUS	current
			::= { hmWanMbusBD 45 }

hmWanMbusBDVIF14		OBJECT-TYPE
			SYNTAX	INTEGER
			MAX-ACCESS	read-only
			STATUS	current
			::= { hmWanMbusBD 46 }

hmWanMbusBDValue14		OBJECT-TYPE
			SYNTAX	INTEGER
			MAX-ACCESS	read-only
			STATUS	current
			::= { hmWanMbusBD 47 }

hmWanMbusBDVIF15		OBJECT-TYPE
			SYNTAX	INTEGER
			MAX-ACCESS	read-only
			STATUS	current
			::= { hmWanMbusBD 48 }

hmWanMbusBDValue15		OBJECT-TYPE
			SYNTAX	INTEGER
			MAX-ACCESS	read-only
			STATUS	current
			::= { hmWanMbusBD 49 }

hmWanMbusBDVIF16		OBJECT-TYPE
			SYNTAX	INTEGER
			MAX-ACCESS	read-only
			STATUS	current
			::= { hmWanMbusBD 50 }

hmWanMbusBDValue16		OBJECT-TYPE
			SYNTAX	INTEGER
			MAX-ACCESS	read-only
			STATUS	current
			::= { hmWanMbusBD 51 }

hmWanMbusBDVIF17		OBJECT-TYPE
			SYNTAX	INTEGER
			MAX-ACCESS	read-only
			STATUS	current
			::= { hmWanMbusBD 52 }

hmWanMbusBDValue17		OBJECT-TYPE
			SYNTAX	INTEGER
			MAX-ACCESS	read-only
			STATUS	current
			::= { hmWanMbusBD 53 }

hmWanMbusBDVIF18		OBJECT-TYPE
			SYNTAX	INTEGER
			MAX-ACCESS	read-only
			STATUS	current
			::= { hmWanMbusBD 54 }

hmWanMbusBDValue18		OBJECT-TYPE
			SYNTAX	INTEGER
			MAX-ACCESS	read-only
			STATUS	current
			::= { hmWanMbusBD 55 }

hmWanMbusBDVIF19		OBJECT-TYPE
			SYNTAX	INTEGER
			MAX-ACCESS	read-only
			STATUS	current
			::= { hmWanMbusBD 56 }

hmWanMbusBDValue19		OBJECT-TYPE
			SYNTAX	INTEGER
			MAX-ACCESS	read-only
			STATUS	current
			::= { hmWanMbusBD 57 }

hmWanMbusBDVIF1A		OBJECT-TYPE
			SYNTAX	INTEGER
			MAX-ACCESS	read-only
			STATUS	current
			::= { hmWanMbusBD 58 }

hmWanMbusBDValue1A		OBJECT-TYPE
			SYNTAX	INTEGER
			MAX-ACCESS	read-only
			STATUS	current
			::= { hmWanMbusBD 59 }

hmWanMbusBDVIF1B		OBJECT-TYPE
			SYNTAX	INTEGER
			MAX-ACCESS	read-only
			STATUS	current
			::= { hmWanMbusBD 60 }

hmWanMbusBDValue1B		OBJECT-TYPE
			SYNTAX	INTEGER
			MAX-ACCESS	read-only
			STATUS	current
			::= { hmWanMbusBD 61 }

hmWanMbusBDVIF1C		OBJECT-TYPE
			SYNTAX	INTEGER
			MAX-ACCESS	read-only
			STATUS	current
			::= { hmWanMbusBD 62 }

hmWanMbusBDValue1C		OBJECT-TYPE
			SYNTAX	INTEGER
			MAX-ACCESS	read-only
			STATUS	current
			::= { hmWanMbusBD 63 }

hmWanMbusBDVIF1D		OBJECT-TYPE
			SYNTAX	INTEGER
			MAX-ACCESS	read-only
			STATUS	current
			::= { hmWanMbusBD 64 }

hmWanMbusBDValue1D		OBJECT-TYPE
			SYNTAX	INTEGER
			MAX-ACCESS	read-only
			STATUS	current
			::= { hmWanMbusBD 65 }

hmWanMbusBDVIF1E		OBJECT-TYPE
			SYNTAX	INTEGER
			MAX-ACCESS	read-only
			STATUS	current
			::= { hmWanMbusBD 66 }

hmWanMbusBDValue1E		OBJECT-TYPE
			SYNTAX	INTEGER
			MAX-ACCESS	read-only
			STATUS	current
			::= { hmWanMbusBD 67 }

hmWanMbusBDVIF1F		OBJECT-TYPE
			SYNTAX	INTEGER
			MAX-ACCESS	read-only
			STATUS	current
			::= { hmWanMbusBD 68 }

hmWanMbusBDValue1F		OBJECT-TYPE
			SYNTAX	INTEGER
			MAX-ACCESS	read-only
			STATUS	current
			::= { hmWanMbusBD 69 }

hmWanMbusBDVIF20		OBJECT-TYPE
			SYNTAX	INTEGER
			MAX-ACCESS	read-only
			STATUS	current
			::= { hmWanMbusBD 70 }

hmWanMbusBDValue20		OBJECT-TYPE
			SYNTAX	INTEGER
			MAX-ACCESS	read-only
			STATUS	current
			::= { hmWanMbusBD 71 }

hmWanMbusBDVIF21		OBJECT-TYPE
			SYNTAX	INTEGER
			MAX-ACCESS	read-only
			STATUS	current
			::= { hmWanMbusBD 72 }

hmWanMbusBDValue21		OBJECT-TYPE
			SYNTAX	INTEGER
			MAX-ACCESS	read-only
			STATUS	current
			::= { hmWanMbusBD 73 }

hmWanMbusBDVIF22		OBJECT-TYPE
			SYNTAX	INTEGER
			MAX-ACCESS	read-only
			STATUS	current
			::= { hmWanMbusBD 74 }

hmWanMbusBDValue22		OBJECT-TYPE
			SYNTAX	INTEGER
			MAX-ACCESS	read-only
			STATUS	current
			::= { hmWanMbusBD 75 }

hmWanMbusBDVIF23		OBJECT-TYPE
			SYNTAX	INTEGER
			MAX-ACCESS	read-only
			STATUS	current
			::= { hmWanMbusBD 76 }

hmWanMbusBDValue23		OBJECT-TYPE
			SYNTAX	INTEGER
			MAX-ACCESS	read-only
			STATUS	current
			::= { hmWanMbusBD 77 }

hmWanMbusBDVIF24		OBJECT-TYPE
			SYNTAX	INTEGER
			MAX-ACCESS	read-only
			STATUS	current
			::= { hmWanMbusBD 78 }

hmWanMbusBDValue24		OBJECT-TYPE
			SYNTAX	INTEGER
			MAX-ACCESS	read-only
			STATUS	current
			::= { hmWanMbusBD 79 }

hmWanMbusBDVIF25		OBJECT-TYPE
			SYNTAX	INTEGER
			MAX-ACCESS	read-only
			STATUS	current
			::= { hmWanMbusBD 80 }

hmWanMbusBDValue25		OBJECT-TYPE
			SYNTAX	INTEGER
			MAX-ACCESS	read-only
			STATUS	current
			::= { hmWanMbusBD 81 }

hmWanMbusBDVIF26		OBJECT-TYPE
			SYNTAX	INTEGER
			MAX-ACCESS	read-only
			STATUS	current
			::= { hmWanMbusBD 82 }

hmWanMbusBDValue26		OBJECT-TYPE
			SYNTAX	INTEGER
			MAX-ACCESS	read-only
			STATUS	current
			::= { hmWanMbusBD 83 }

hmWanMbusBDVIF27		OBJECT-TYPE
			SYNTAX	INTEGER
			MAX-ACCESS	read-only
			STATUS	current
			::= { hmWanMbusBD 84 }

hmWanMbusBDValue27		OBJECT-TYPE
			SYNTAX	INTEGER
			MAX-ACCESS	read-only
			STATUS	current
			::= { hmWanMbusBD 85 }

hmWanMbusBDVIF28		OBJECT-TYPE
			SYNTAX	INTEGER
			MAX-ACCESS	read-only
			STATUS	current
			::= { hmWanMbusBD 86 }

hmWanMbusBDValue28		OBJECT-TYPE
			SYNTAX	INTEGER
			MAX-ACCESS	read-only
			STATUS	current
			::= { hmWanMbusBD 87 }

hmWanMbusBDVIF29		OBJECT-TYPE
			SYNTAX	INTEGER
			MAX-ACCESS	read-only
			STATUS	current
			::= { hmWanMbusBD 88 }

hmWanMbusBDValue29		OBJECT-TYPE
			SYNTAX	INTEGER
			MAX-ACCESS	read-only
			STATUS	current
			::= { hmWanMbusBD 89 }

hmWanMbusBDVIF2A		OBJECT-TYPE
			SYNTAX	INTEGER
			MAX-ACCESS	read-only
			STATUS	current
			::= { hmWanMbusBD 90 }

hmWanMbusBDValue2A		OBJECT-TYPE
			SYNTAX	INTEGER
			MAX-ACCESS	read-only
			STATUS	current
			::= { hmWanMbusBD 91 }

hmWanMbusBDVIF2B		OBJECT-TYPE
			SYNTAX	INTEGER
			MAX-ACCESS	read-only
			STATUS	current
			::= { hmWanMbusBD 92 }

hmWanMbusBDValue2B		OBJECT-TYPE
			SYNTAX	INTEGER
			MAX-ACCESS	read-only
			STATUS	current
			::= { hmWanMbusBD 93 }

hmWanMbusBDVIF2C		OBJECT-TYPE
			SYNTAX	INTEGER
			MAX-ACCESS	read-only
			STATUS	current
			::= { hmWanMbusBD 94 }

hmWanMbusBDValue2C		OBJECT-TYPE
			SYNTAX	INTEGER
			MAX-ACCESS	read-only
			STATUS	current
			::= { hmWanMbusBD 95 }

hmWanMbusBDVIF2D		OBJECT-TYPE
			SYNTAX	INTEGER
			MAX-ACCESS	read-only
			STATUS	current
			::= { hmWanMbusBD 96 }

hmWanMbusBDValue2D		OBJECT-TYPE
			SYNTAX	INTEGER
			MAX-ACCESS	read-only
			STATUS	current
			::= { hmWanMbusBD 97 }

hmWanMbusBDVIF2E		OBJECT-TYPE
			SYNTAX	INTEGER
			MAX-ACCESS	read-only
			STATUS	current
			::= { hmWanMbusBD 98 }

hmWanMbusBDValue2E		OBJECT-TYPE
			SYNTAX	INTEGER
			MAX-ACCESS	read-only
			STATUS	current
			::= { hmWanMbusBD 99 }

hmWanMbusBDVIF2F		OBJECT-TYPE
			SYNTAX	INTEGER
			MAX-ACCESS	read-only
			STATUS	current
			::= { hmWanMbusBD 100 }

hmWanMbusBDValue2F		OBJECT-TYPE
			SYNTAX	INTEGER
			MAX-ACCESS	read-only
			STATUS	current
			::= { hmWanMbusBD 101 }

hmWanMbusBE			OBJECT IDENTIFIER ::= { hmWanMbus 190 }

hmWanMbusBEIdNumber		OBJECT-TYPE
			SYNTAX	Gauge32
			MAX-ACCESS	read-only
			STATUS	current
			::= { hmWanMbusBE 1 }

hmWanMbusBEManufacturer	OBJECT-TYPE
			SYNTAX	Gauge32
			MAX-ACCESS	read-only
			STATUS	current
			::= { hmWanMbusBE 2 }

hmWanMbusBEVersion		OBJECT-TYPE
			SYNTAX	Gauge32
			MAX-ACCESS	read-only
			STATUS	current
			::= { hmWanMbusBE 3 }

hmWanMbusBEMedium		OBJECT-TYPE
			SYNTAX	Gauge32
			MAX-ACCESS	read-only
			STATUS	current
			::= { hmWanMbusBE 4 }

hmWanMbusBEStatus		OBJECT-TYPE
			SYNTAX	Gauge32
			MAX-ACCESS	read-only
			STATUS	current
			::= { hmWanMbusBE 5 }

hmWanMbusBEVIF00		OBJECT-TYPE
			SYNTAX	INTEGER
			MAX-ACCESS	read-only
			STATUS	current
			::= { hmWanMbusBE 6 }

hmWanMbusBEValue00		OBJECT-TYPE
			SYNTAX	INTEGER
			MAX-ACCESS	read-only
			STATUS	current
			::= { hmWanMbusBE 7 }

hmWanMbusBEVIF01		OBJECT-TYPE
			SYNTAX	INTEGER
			MAX-ACCESS	read-only
			STATUS	current
			::= { hmWanMbusBE 8 }

hmWanMbusBEValue01		OBJECT-TYPE
			SYNTAX	INTEGER
			MAX-ACCESS	read-only
			STATUS	current
			::= { hmWanMbusBE 9 }

hmWanMbusBEVIF02		OBJECT-TYPE
			SYNTAX	INTEGER
			MAX-ACCESS	read-only
			STATUS	current
			::= { hmWanMbusBE 10 }

hmWanMbusBEValue02		OBJECT-TYPE
			SYNTAX	INTEGER
			MAX-ACCESS	read-only
			STATUS	current
			::= { hmWanMbusBE 11 }

hmWanMbusBEVIF03		OBJECT-TYPE
			SYNTAX	INTEGER
			MAX-ACCESS	read-only
			STATUS	current
			::= { hmWanMbusBE 12 }

hmWanMbusBEValue03		OBJECT-TYPE
			SYNTAX	INTEGER
			MAX-ACCESS	read-only
			STATUS	current
			::= { hmWanMbusBE 13 }

hmWanMbusBEVIF04		OBJECT-TYPE
			SYNTAX	INTEGER
			MAX-ACCESS	read-only
			STATUS	current
			::= { hmWanMbusBE 14 }

hmWanMbusBEValue04		OBJECT-TYPE
			SYNTAX	INTEGER
			MAX-ACCESS	read-only
			STATUS	current
			::= { hmWanMbusBE 15 }

hmWanMbusBEVIF05		OBJECT-TYPE
			SYNTAX	INTEGER
			MAX-ACCESS	read-only
			STATUS	current
			::= { hmWanMbusBE 16 }

hmWanMbusBEValue05		OBJECT-TYPE
			SYNTAX	INTEGER
			MAX-ACCESS	read-only
			STATUS	current
			::= { hmWanMbusBE 17 }

hmWanMbusBEVIF06		OBJECT-TYPE
			SYNTAX	INTEGER
			MAX-ACCESS	read-only
			STATUS	current
			::= { hmWanMbusBE 18 }

hmWanMbusBEValue06		OBJECT-TYPE
			SYNTAX	INTEGER
			MAX-ACCESS	read-only
			STATUS	current
			::= { hmWanMbusBE 19 }

hmWanMbusBEVIF07		OBJECT-TYPE
			SYNTAX	INTEGER
			MAX-ACCESS	read-only
			STATUS	current
			::= { hmWanMbusBE 20 }

hmWanMbusBEValue07		OBJECT-TYPE
			SYNTAX	INTEGER
			MAX-ACCESS	read-only
			STATUS	current
			::= { hmWanMbusBE 21 }

hmWanMbusBEVIF08		OBJECT-TYPE
			SYNTAX	INTEGER
			MAX-ACCESS	read-only
			STATUS	current
			::= { hmWanMbusBE 22 }

hmWanMbusBEValue08		OBJECT-TYPE
			SYNTAX	INTEGER
			MAX-ACCESS	read-only
			STATUS	current
			::= { hmWanMbusBE 23 }

hmWanMbusBEVIF09		OBJECT-TYPE
			SYNTAX	INTEGER
			MAX-ACCESS	read-only
			STATUS	current
			::= { hmWanMbusBE 24 }

hmWanMbusBEValue09		OBJECT-TYPE
			SYNTAX	INTEGER
			MAX-ACCESS	read-only
			STATUS	current
			::= { hmWanMbusBE 25 }

hmWanMbusBEVIF0A		OBJECT-TYPE
			SYNTAX	INTEGER
			MAX-ACCESS	read-only
			STATUS	current
			::= { hmWanMbusBE 26 }

hmWanMbusBEValue0A		OBJECT-TYPE
			SYNTAX	INTEGER
			MAX-ACCESS	read-only
			STATUS	current
			::= { hmWanMbusBE 27 }

hmWanMbusBEVIF0B		OBJECT-TYPE
			SYNTAX	INTEGER
			MAX-ACCESS	read-only
			STATUS	current
			::= { hmWanMbusBE 28 }

hmWanMbusBEValue0B		OBJECT-TYPE
			SYNTAX	INTEGER
			MAX-ACCESS	read-only
			STATUS	current
			::= { hmWanMbusBE 29 }

hmWanMbusBEVIF0C		OBJECT-TYPE
			SYNTAX	INTEGER
			MAX-ACCESS	read-only
			STATUS	current
			::= { hmWanMbusBE 30 }

hmWanMbusBEValue0C		OBJECT-TYPE
			SYNTAX	INTEGER
			MAX-ACCESS	read-only
			STATUS	current
			::= { hmWanMbusBE 31 }

hmWanMbusBEVIF0D		OBJECT-TYPE
			SYNTAX	INTEGER
			MAX-ACCESS	read-only
			STATUS	current
			::= { hmWanMbusBE 32 }

hmWanMbusBEValue0D		OBJECT-TYPE
			SYNTAX	INTEGER
			MAX-ACCESS	read-only
			STATUS	current
			::= { hmWanMbusBE 33 }

hmWanMbusBEVIF0E		OBJECT-TYPE
			SYNTAX	INTEGER
			MAX-ACCESS	read-only
			STATUS	current
			::= { hmWanMbusBE 34 }

hmWanMbusBEValue0E		OBJECT-TYPE
			SYNTAX	INTEGER
			MAX-ACCESS	read-only
			STATUS	current
			::= { hmWanMbusBE 35 }

hmWanMbusBEVIF0F		OBJECT-TYPE
			SYNTAX	INTEGER
			MAX-ACCESS	read-only
			STATUS	current
			::= { hmWanMbusBE 36 }

hmWanMbusBEValue0F		OBJECT-TYPE
			SYNTAX	INTEGER
			MAX-ACCESS	read-only
			STATUS	current
			::= { hmWanMbusBE 37 }

hmWanMbusBEVIF10		OBJECT-TYPE
			SYNTAX	INTEGER
			MAX-ACCESS	read-only
			STATUS	current
			::= { hmWanMbusBE 38 }

hmWanMbusBEValue10		OBJECT-TYPE
			SYNTAX	INTEGER
			MAX-ACCESS	read-only
			STATUS	current
			::= { hmWanMbusBE 39 }

hmWanMbusBEVIF11		OBJECT-TYPE
			SYNTAX	INTEGER
			MAX-ACCESS	read-only
			STATUS	current
			::= { hmWanMbusBE 40 }

hmWanMbusBEValue11		OBJECT-TYPE
			SYNTAX	INTEGER
			MAX-ACCESS	read-only
			STATUS	current
			::= { hmWanMbusBE 41 }

hmWanMbusBEVIF12		OBJECT-TYPE
			SYNTAX	INTEGER
			MAX-ACCESS	read-only
			STATUS	current
			::= { hmWanMbusBE 42 }

hmWanMbusBEValue12		OBJECT-TYPE
			SYNTAX	INTEGER
			MAX-ACCESS	read-only
			STATUS	current
			::= { hmWanMbusBE 43 }

hmWanMbusBEVIF13		OBJECT-TYPE
			SYNTAX	INTEGER
			MAX-ACCESS	read-only
			STATUS	current
			::= { hmWanMbusBE 44 }

hmWanMbusBEValue13		OBJECT-TYPE
			SYNTAX	INTEGER
			MAX-ACCESS	read-only
			STATUS	current
			::= { hmWanMbusBE 45 }

hmWanMbusBEVIF14		OBJECT-TYPE
			SYNTAX	INTEGER
			MAX-ACCESS	read-only
			STATUS	current
			::= { hmWanMbusBE 46 }

hmWanMbusBEValue14		OBJECT-TYPE
			SYNTAX	INTEGER
			MAX-ACCESS	read-only
			STATUS	current
			::= { hmWanMbusBE 47 }

hmWanMbusBEVIF15		OBJECT-TYPE
			SYNTAX	INTEGER
			MAX-ACCESS	read-only
			STATUS	current
			::= { hmWanMbusBE 48 }

hmWanMbusBEValue15		OBJECT-TYPE
			SYNTAX	INTEGER
			MAX-ACCESS	read-only
			STATUS	current
			::= { hmWanMbusBE 49 }

hmWanMbusBEVIF16		OBJECT-TYPE
			SYNTAX	INTEGER
			MAX-ACCESS	read-only
			STATUS	current
			::= { hmWanMbusBE 50 }

hmWanMbusBEValue16		OBJECT-TYPE
			SYNTAX	INTEGER
			MAX-ACCESS	read-only
			STATUS	current
			::= { hmWanMbusBE 51 }

hmWanMbusBEVIF17		OBJECT-TYPE
			SYNTAX	INTEGER
			MAX-ACCESS	read-only
			STATUS	current
			::= { hmWanMbusBE 52 }

hmWanMbusBEValue17		OBJECT-TYPE
			SYNTAX	INTEGER
			MAX-ACCESS	read-only
			STATUS	current
			::= { hmWanMbusBE 53 }

hmWanMbusBEVIF18		OBJECT-TYPE
			SYNTAX	INTEGER
			MAX-ACCESS	read-only
			STATUS	current
			::= { hmWanMbusBE 54 }

hmWanMbusBEValue18		OBJECT-TYPE
			SYNTAX	INTEGER
			MAX-ACCESS	read-only
			STATUS	current
			::= { hmWanMbusBE 55 }

hmWanMbusBEVIF19		OBJECT-TYPE
			SYNTAX	INTEGER
			MAX-ACCESS	read-only
			STATUS	current
			::= { hmWanMbusBE 56 }

hmWanMbusBEValue19		OBJECT-TYPE
			SYNTAX	INTEGER
			MAX-ACCESS	read-only
			STATUS	current
			::= { hmWanMbusBE 57 }

hmWanMbusBEVIF1A		OBJECT-TYPE
			SYNTAX	INTEGER
			MAX-ACCESS	read-only
			STATUS	current
			::= { hmWanMbusBE 58 }

hmWanMbusBEValue1A		OBJECT-TYPE
			SYNTAX	INTEGER
			MAX-ACCESS	read-only
			STATUS	current
			::= { hmWanMbusBE 59 }

hmWanMbusBEVIF1B		OBJECT-TYPE
			SYNTAX	INTEGER
			MAX-ACCESS	read-only
			STATUS	current
			::= { hmWanMbusBE 60 }

hmWanMbusBEValue1B		OBJECT-TYPE
			SYNTAX	INTEGER
			MAX-ACCESS	read-only
			STATUS	current
			::= { hmWanMbusBE 61 }

hmWanMbusBEVIF1C		OBJECT-TYPE
			SYNTAX	INTEGER
			MAX-ACCESS	read-only
			STATUS	current
			::= { hmWanMbusBE 62 }

hmWanMbusBEValue1C		OBJECT-TYPE
			SYNTAX	INTEGER
			MAX-ACCESS	read-only
			STATUS	current
			::= { hmWanMbusBE 63 }

hmWanMbusBEVIF1D		OBJECT-TYPE
			SYNTAX	INTEGER
			MAX-ACCESS	read-only
			STATUS	current
			::= { hmWanMbusBE 64 }

hmWanMbusBEValue1D		OBJECT-TYPE
			SYNTAX	INTEGER
			MAX-ACCESS	read-only
			STATUS	current
			::= { hmWanMbusBE 65 }

hmWanMbusBEVIF1E		OBJECT-TYPE
			SYNTAX	INTEGER
			MAX-ACCESS	read-only
			STATUS	current
			::= { hmWanMbusBE 66 }

hmWanMbusBEValue1E		OBJECT-TYPE
			SYNTAX	INTEGER
			MAX-ACCESS	read-only
			STATUS	current
			::= { hmWanMbusBE 67 }

hmWanMbusBEVIF1F		OBJECT-TYPE
			SYNTAX	INTEGER
			MAX-ACCESS	read-only
			STATUS	current
			::= { hmWanMbusBE 68 }

hmWanMbusBEValue1F		OBJECT-TYPE
			SYNTAX	INTEGER
			MAX-ACCESS	read-only
			STATUS	current
			::= { hmWanMbusBE 69 }

hmWanMbusBEVIF20		OBJECT-TYPE
			SYNTAX	INTEGER
			MAX-ACCESS	read-only
			STATUS	current
			::= { hmWanMbusBE 70 }

hmWanMbusBEValue20		OBJECT-TYPE
			SYNTAX	INTEGER
			MAX-ACCESS	read-only
			STATUS	current
			::= { hmWanMbusBE 71 }

hmWanMbusBEVIF21		OBJECT-TYPE
			SYNTAX	INTEGER
			MAX-ACCESS	read-only
			STATUS	current
			::= { hmWanMbusBE 72 }

hmWanMbusBEValue21		OBJECT-TYPE
			SYNTAX	INTEGER
			MAX-ACCESS	read-only
			STATUS	current
			::= { hmWanMbusBE 73 }

hmWanMbusBEVIF22		OBJECT-TYPE
			SYNTAX	INTEGER
			MAX-ACCESS	read-only
			STATUS	current
			::= { hmWanMbusBE 74 }

hmWanMbusBEValue22		OBJECT-TYPE
			SYNTAX	INTEGER
			MAX-ACCESS	read-only
			STATUS	current
			::= { hmWanMbusBE 75 }

hmWanMbusBEVIF23		OBJECT-TYPE
			SYNTAX	INTEGER
			MAX-ACCESS	read-only
			STATUS	current
			::= { hmWanMbusBE 76 }

hmWanMbusBEValue23		OBJECT-TYPE
			SYNTAX	INTEGER
			MAX-ACCESS	read-only
			STATUS	current
			::= { hmWanMbusBE 77 }

hmWanMbusBEVIF24		OBJECT-TYPE
			SYNTAX	INTEGER
			MAX-ACCESS	read-only
			STATUS	current
			::= { hmWanMbusBE 78 }

hmWanMbusBEValue24		OBJECT-TYPE
			SYNTAX	INTEGER
			MAX-ACCESS	read-only
			STATUS	current
			::= { hmWanMbusBE 79 }

hmWanMbusBEVIF25		OBJECT-TYPE
			SYNTAX	INTEGER
			MAX-ACCESS	read-only
			STATUS	current
			::= { hmWanMbusBE 80 }

hmWanMbusBEValue25		OBJECT-TYPE
			SYNTAX	INTEGER
			MAX-ACCESS	read-only
			STATUS	current
			::= { hmWanMbusBE 81 }

hmWanMbusBEVIF26		OBJECT-TYPE
			SYNTAX	INTEGER
			MAX-ACCESS	read-only
			STATUS	current
			::= { hmWanMbusBE 82 }

hmWanMbusBEValue26		OBJECT-TYPE
			SYNTAX	INTEGER
			MAX-ACCESS	read-only
			STATUS	current
			::= { hmWanMbusBE 83 }

hmWanMbusBEVIF27		OBJECT-TYPE
			SYNTAX	INTEGER
			MAX-ACCESS	read-only
			STATUS	current
			::= { hmWanMbusBE 84 }

hmWanMbusBEValue27		OBJECT-TYPE
			SYNTAX	INTEGER
			MAX-ACCESS	read-only
			STATUS	current
			::= { hmWanMbusBE 85 }

hmWanMbusBEVIF28		OBJECT-TYPE
			SYNTAX	INTEGER
			MAX-ACCESS	read-only
			STATUS	current
			::= { hmWanMbusBE 86 }

hmWanMbusBEValue28		OBJECT-TYPE
			SYNTAX	INTEGER
			MAX-ACCESS	read-only
			STATUS	current
			::= { hmWanMbusBE 87 }

hmWanMbusBEVIF29		OBJECT-TYPE
			SYNTAX	INTEGER
			MAX-ACCESS	read-only
			STATUS	current
			::= { hmWanMbusBE 88 }

hmWanMbusBEValue29		OBJECT-TYPE
			SYNTAX	INTEGER
			MAX-ACCESS	read-only
			STATUS	current
			::= { hmWanMbusBE 89 }

hmWanMbusBEVIF2A		OBJECT-TYPE
			SYNTAX	INTEGER
			MAX-ACCESS	read-only
			STATUS	current
			::= { hmWanMbusBE 90 }

hmWanMbusBEValue2A		OBJECT-TYPE
			SYNTAX	INTEGER
			MAX-ACCESS	read-only
			STATUS	current
			::= { hmWanMbusBE 91 }

hmWanMbusBEVIF2B		OBJECT-TYPE
			SYNTAX	INTEGER
			MAX-ACCESS	read-only
			STATUS	current
			::= { hmWanMbusBE 92 }

hmWanMbusBEValue2B		OBJECT-TYPE
			SYNTAX	INTEGER
			MAX-ACCESS	read-only
			STATUS	current
			::= { hmWanMbusBE 93 }

hmWanMbusBEVIF2C		OBJECT-TYPE
			SYNTAX	INTEGER
			MAX-ACCESS	read-only
			STATUS	current
			::= { hmWanMbusBE 94 }

hmWanMbusBEValue2C		OBJECT-TYPE
			SYNTAX	INTEGER
			MAX-ACCESS	read-only
			STATUS	current
			::= { hmWanMbusBE 95 }

hmWanMbusBEVIF2D		OBJECT-TYPE
			SYNTAX	INTEGER
			MAX-ACCESS	read-only
			STATUS	current
			::= { hmWanMbusBE 96 }

hmWanMbusBEValue2D		OBJECT-TYPE
			SYNTAX	INTEGER
			MAX-ACCESS	read-only
			STATUS	current
			::= { hmWanMbusBE 97 }

hmWanMbusBEVIF2E		OBJECT-TYPE
			SYNTAX	INTEGER
			MAX-ACCESS	read-only
			STATUS	current
			::= { hmWanMbusBE 98 }

hmWanMbusBEValue2E		OBJECT-TYPE
			SYNTAX	INTEGER
			MAX-ACCESS	read-only
			STATUS	current
			::= { hmWanMbusBE 99 }

hmWanMbusBEVIF2F		OBJECT-TYPE
			SYNTAX	INTEGER
			MAX-ACCESS	read-only
			STATUS	current
			::= { hmWanMbusBE 100 }

hmWanMbusBEValue2F		OBJECT-TYPE
			SYNTAX	INTEGER
			MAX-ACCESS	read-only
			STATUS	current
			::= { hmWanMbusBE 101 }

hmWanMbusBF			OBJECT IDENTIFIER ::= { hmWanMbus 191 }

hmWanMbusBFIdNumber		OBJECT-TYPE
			SYNTAX	Gauge32
			MAX-ACCESS	read-only
			STATUS	current
			::= { hmWanMbusBF 1 }

hmWanMbusBFManufacturer	OBJECT-TYPE
			SYNTAX	Gauge32
			MAX-ACCESS	read-only
			STATUS	current
			::= { hmWanMbusBF 2 }

hmWanMbusBFVersion		OBJECT-TYPE
			SYNTAX	Gauge32
			MAX-ACCESS	read-only
			STATUS	current
			::= { hmWanMbusBF 3 }

hmWanMbusBFMedium		OBJECT-TYPE
			SYNTAX	Gauge32
			MAX-ACCESS	read-only
			STATUS	current
			::= { hmWanMbusBF 4 }

hmWanMbusBFStatus		OBJECT-TYPE
			SYNTAX	Gauge32
			MAX-ACCESS	read-only
			STATUS	current
			::= { hmWanMbusBF 5 }

hmWanMbusBFVIF00		OBJECT-TYPE
			SYNTAX	INTEGER
			MAX-ACCESS	read-only
			STATUS	current
			::= { hmWanMbusBF 6 }

hmWanMbusBFValue00		OBJECT-TYPE
			SYNTAX	INTEGER
			MAX-ACCESS	read-only
			STATUS	current
			::= { hmWanMbusBF 7 }

hmWanMbusBFVIF01		OBJECT-TYPE
			SYNTAX	INTEGER
			MAX-ACCESS	read-only
			STATUS	current
			::= { hmWanMbusBF 8 }

hmWanMbusBFValue01		OBJECT-TYPE
			SYNTAX	INTEGER
			MAX-ACCESS	read-only
			STATUS	current
			::= { hmWanMbusBF 9 }

hmWanMbusBFVIF02		OBJECT-TYPE
			SYNTAX	INTEGER
			MAX-ACCESS	read-only
			STATUS	current
			::= { hmWanMbusBF 10 }

hmWanMbusBFValue02		OBJECT-TYPE
			SYNTAX	INTEGER
			MAX-ACCESS	read-only
			STATUS	current
			::= { hmWanMbusBF 11 }

hmWanMbusBFVIF03		OBJECT-TYPE
			SYNTAX	INTEGER
			MAX-ACCESS	read-only
			STATUS	current
			::= { hmWanMbusBF 12 }

hmWanMbusBFValue03		OBJECT-TYPE
			SYNTAX	INTEGER
			MAX-ACCESS	read-only
			STATUS	current
			::= { hmWanMbusBF 13 }

hmWanMbusBFVIF04		OBJECT-TYPE
			SYNTAX	INTEGER
			MAX-ACCESS	read-only
			STATUS	current
			::= { hmWanMbusBF 14 }

hmWanMbusBFValue04		OBJECT-TYPE
			SYNTAX	INTEGER
			MAX-ACCESS	read-only
			STATUS	current
			::= { hmWanMbusBF 15 }

hmWanMbusBFVIF05		OBJECT-TYPE
			SYNTAX	INTEGER
			MAX-ACCESS	read-only
			STATUS	current
			::= { hmWanMbusBF 16 }

hmWanMbusBFValue05		OBJECT-TYPE
			SYNTAX	INTEGER
			MAX-ACCESS	read-only
			STATUS	current
			::= { hmWanMbusBF 17 }

hmWanMbusBFVIF06		OBJECT-TYPE
			SYNTAX	INTEGER
			MAX-ACCESS	read-only
			STATUS	current
			::= { hmWanMbusBF 18 }

hmWanMbusBFValue06		OBJECT-TYPE
			SYNTAX	INTEGER
			MAX-ACCESS	read-only
			STATUS	current
			::= { hmWanMbusBF 19 }

hmWanMbusBFVIF07		OBJECT-TYPE
			SYNTAX	INTEGER
			MAX-ACCESS	read-only
			STATUS	current
			::= { hmWanMbusBF 20 }

hmWanMbusBFValue07		OBJECT-TYPE
			SYNTAX	INTEGER
			MAX-ACCESS	read-only
			STATUS	current
			::= { hmWanMbusBF 21 }

hmWanMbusBFVIF08		OBJECT-TYPE
			SYNTAX	INTEGER
			MAX-ACCESS	read-only
			STATUS	current
			::= { hmWanMbusBF 22 }

hmWanMbusBFValue08		OBJECT-TYPE
			SYNTAX	INTEGER
			MAX-ACCESS	read-only
			STATUS	current
			::= { hmWanMbusBF 23 }

hmWanMbusBFVIF09		OBJECT-TYPE
			SYNTAX	INTEGER
			MAX-ACCESS	read-only
			STATUS	current
			::= { hmWanMbusBF 24 }

hmWanMbusBFValue09		OBJECT-TYPE
			SYNTAX	INTEGER
			MAX-ACCESS	read-only
			STATUS	current
			::= { hmWanMbusBF 25 }

hmWanMbusBFVIF0A		OBJECT-TYPE
			SYNTAX	INTEGER
			MAX-ACCESS	read-only
			STATUS	current
			::= { hmWanMbusBF 26 }

hmWanMbusBFValue0A		OBJECT-TYPE
			SYNTAX	INTEGER
			MAX-ACCESS	read-only
			STATUS	current
			::= { hmWanMbusBF 27 }

hmWanMbusBFVIF0B		OBJECT-TYPE
			SYNTAX	INTEGER
			MAX-ACCESS	read-only
			STATUS	current
			::= { hmWanMbusBF 28 }

hmWanMbusBFValue0B		OBJECT-TYPE
			SYNTAX	INTEGER
			MAX-ACCESS	read-only
			STATUS	current
			::= { hmWanMbusBF 29 }

hmWanMbusBFVIF0C		OBJECT-TYPE
			SYNTAX	INTEGER
			MAX-ACCESS	read-only
			STATUS	current
			::= { hmWanMbusBF 30 }

hmWanMbusBFValue0C		OBJECT-TYPE
			SYNTAX	INTEGER
			MAX-ACCESS	read-only
			STATUS	current
			::= { hmWanMbusBF 31 }

hmWanMbusBFVIF0D		OBJECT-TYPE
			SYNTAX	INTEGER
			MAX-ACCESS	read-only
			STATUS	current
			::= { hmWanMbusBF 32 }

hmWanMbusBFValue0D		OBJECT-TYPE
			SYNTAX	INTEGER
			MAX-ACCESS	read-only
			STATUS	current
			::= { hmWanMbusBF 33 }

hmWanMbusBFVIF0E		OBJECT-TYPE
			SYNTAX	INTEGER
			MAX-ACCESS	read-only
			STATUS	current
			::= { hmWanMbusBF 34 }

hmWanMbusBFValue0E		OBJECT-TYPE
			SYNTAX	INTEGER
			MAX-ACCESS	read-only
			STATUS	current
			::= { hmWanMbusBF 35 }

hmWanMbusBFVIF0F		OBJECT-TYPE
			SYNTAX	INTEGER
			MAX-ACCESS	read-only
			STATUS	current
			::= { hmWanMbusBF 36 }

hmWanMbusBFValue0F		OBJECT-TYPE
			SYNTAX	INTEGER
			MAX-ACCESS	read-only
			STATUS	current
			::= { hmWanMbusBF 37 }

hmWanMbusBFVIF10		OBJECT-TYPE
			SYNTAX	INTEGER
			MAX-ACCESS	read-only
			STATUS	current
			::= { hmWanMbusBF 38 }

hmWanMbusBFValue10		OBJECT-TYPE
			SYNTAX	INTEGER
			MAX-ACCESS	read-only
			STATUS	current
			::= { hmWanMbusBF 39 }

hmWanMbusBFVIF11		OBJECT-TYPE
			SYNTAX	INTEGER
			MAX-ACCESS	read-only
			STATUS	current
			::= { hmWanMbusBF 40 }

hmWanMbusBFValue11		OBJECT-TYPE
			SYNTAX	INTEGER
			MAX-ACCESS	read-only
			STATUS	current
			::= { hmWanMbusBF 41 }

hmWanMbusBFVIF12		OBJECT-TYPE
			SYNTAX	INTEGER
			MAX-ACCESS	read-only
			STATUS	current
			::= { hmWanMbusBF 42 }

hmWanMbusBFValue12		OBJECT-TYPE
			SYNTAX	INTEGER
			MAX-ACCESS	read-only
			STATUS	current
			::= { hmWanMbusBF 43 }

hmWanMbusBFVIF13		OBJECT-TYPE
			SYNTAX	INTEGER
			MAX-ACCESS	read-only
			STATUS	current
			::= { hmWanMbusBF 44 }

hmWanMbusBFValue13		OBJECT-TYPE
			SYNTAX	INTEGER
			MAX-ACCESS	read-only
			STATUS	current
			::= { hmWanMbusBF 45 }

hmWanMbusBFVIF14		OBJECT-TYPE
			SYNTAX	INTEGER
			MAX-ACCESS	read-only
			STATUS	current
			::= { hmWanMbusBF 46 }

hmWanMbusBFValue14		OBJECT-TYPE
			SYNTAX	INTEGER
			MAX-ACCESS	read-only
			STATUS	current
			::= { hmWanMbusBF 47 }

hmWanMbusBFVIF15		OBJECT-TYPE
			SYNTAX	INTEGER
			MAX-ACCESS	read-only
			STATUS	current
			::= { hmWanMbusBF 48 }

hmWanMbusBFValue15		OBJECT-TYPE
			SYNTAX	INTEGER
			MAX-ACCESS	read-only
			STATUS	current
			::= { hmWanMbusBF 49 }

hmWanMbusBFVIF16		OBJECT-TYPE
			SYNTAX	INTEGER
			MAX-ACCESS	read-only
			STATUS	current
			::= { hmWanMbusBF 50 }

hmWanMbusBFValue16		OBJECT-TYPE
			SYNTAX	INTEGER
			MAX-ACCESS	read-only
			STATUS	current
			::= { hmWanMbusBF 51 }

hmWanMbusBFVIF17		OBJECT-TYPE
			SYNTAX	INTEGER
			MAX-ACCESS	read-only
			STATUS	current
			::= { hmWanMbusBF 52 }

hmWanMbusBFValue17		OBJECT-TYPE
			SYNTAX	INTEGER
			MAX-ACCESS	read-only
			STATUS	current
			::= { hmWanMbusBF 53 }

hmWanMbusBFVIF18		OBJECT-TYPE
			SYNTAX	INTEGER
			MAX-ACCESS	read-only
			STATUS	current
			::= { hmWanMbusBF 54 }

hmWanMbusBFValue18		OBJECT-TYPE
			SYNTAX	INTEGER
			MAX-ACCESS	read-only
			STATUS	current
			::= { hmWanMbusBF 55 }

hmWanMbusBFVIF19		OBJECT-TYPE
			SYNTAX	INTEGER
			MAX-ACCESS	read-only
			STATUS	current
			::= { hmWanMbusBF 56 }

hmWanMbusBFValue19		OBJECT-TYPE
			SYNTAX	INTEGER
			MAX-ACCESS	read-only
			STATUS	current
			::= { hmWanMbusBF 57 }

hmWanMbusBFVIF1A		OBJECT-TYPE
			SYNTAX	INTEGER
			MAX-ACCESS	read-only
			STATUS	current
			::= { hmWanMbusBF 58 }

hmWanMbusBFValue1A		OBJECT-TYPE
			SYNTAX	INTEGER
			MAX-ACCESS	read-only
			STATUS	current
			::= { hmWanMbusBF 59 }

hmWanMbusBFVIF1B		OBJECT-TYPE
			SYNTAX	INTEGER
			MAX-ACCESS	read-only
			STATUS	current
			::= { hmWanMbusBF 60 }

hmWanMbusBFValue1B		OBJECT-TYPE
			SYNTAX	INTEGER
			MAX-ACCESS	read-only
			STATUS	current
			::= { hmWanMbusBF 61 }

hmWanMbusBFVIF1C		OBJECT-TYPE
			SYNTAX	INTEGER
			MAX-ACCESS	read-only
			STATUS	current
			::= { hmWanMbusBF 62 }

hmWanMbusBFValue1C		OBJECT-TYPE
			SYNTAX	INTEGER
			MAX-ACCESS	read-only
			STATUS	current
			::= { hmWanMbusBF 63 }

hmWanMbusBFVIF1D		OBJECT-TYPE
			SYNTAX	INTEGER
			MAX-ACCESS	read-only
			STATUS	current
			::= { hmWanMbusBF 64 }

hmWanMbusBFValue1D		OBJECT-TYPE
			SYNTAX	INTEGER
			MAX-ACCESS	read-only
			STATUS	current
			::= { hmWanMbusBF 65 }

hmWanMbusBFVIF1E		OBJECT-TYPE
			SYNTAX	INTEGER
			MAX-ACCESS	read-only
			STATUS	current
			::= { hmWanMbusBF 66 }

hmWanMbusBFValue1E		OBJECT-TYPE
			SYNTAX	INTEGER
			MAX-ACCESS	read-only
			STATUS	current
			::= { hmWanMbusBF 67 }

hmWanMbusBFVIF1F		OBJECT-TYPE
			SYNTAX	INTEGER
			MAX-ACCESS	read-only
			STATUS	current
			::= { hmWanMbusBF 68 }

hmWanMbusBFValue1F		OBJECT-TYPE
			SYNTAX	INTEGER
			MAX-ACCESS	read-only
			STATUS	current
			::= { hmWanMbusBF 69 }

hmWanMbusBFVIF20		OBJECT-TYPE
			SYNTAX	INTEGER
			MAX-ACCESS	read-only
			STATUS	current
			::= { hmWanMbusBF 70 }

hmWanMbusBFValue20		OBJECT-TYPE
			SYNTAX	INTEGER
			MAX-ACCESS	read-only
			STATUS	current
			::= { hmWanMbusBF 71 }

hmWanMbusBFVIF21		OBJECT-TYPE
			SYNTAX	INTEGER
			MAX-ACCESS	read-only
			STATUS	current
			::= { hmWanMbusBF 72 }

hmWanMbusBFValue21		OBJECT-TYPE
			SYNTAX	INTEGER
			MAX-ACCESS	read-only
			STATUS	current
			::= { hmWanMbusBF 73 }

hmWanMbusBFVIF22		OBJECT-TYPE
			SYNTAX	INTEGER
			MAX-ACCESS	read-only
			STATUS	current
			::= { hmWanMbusBF 74 }

hmWanMbusBFValue22		OBJECT-TYPE
			SYNTAX	INTEGER
			MAX-ACCESS	read-only
			STATUS	current
			::= { hmWanMbusBF 75 }

hmWanMbusBFVIF23		OBJECT-TYPE
			SYNTAX	INTEGER
			MAX-ACCESS	read-only
			STATUS	current
			::= { hmWanMbusBF 76 }

hmWanMbusBFValue23		OBJECT-TYPE
			SYNTAX	INTEGER
			MAX-ACCESS	read-only
			STATUS	current
			::= { hmWanMbusBF 77 }

hmWanMbusBFVIF24		OBJECT-TYPE
			SYNTAX	INTEGER
			MAX-ACCESS	read-only
			STATUS	current
			::= { hmWanMbusBF 78 }

hmWanMbusBFValue24		OBJECT-TYPE
			SYNTAX	INTEGER
			MAX-ACCESS	read-only
			STATUS	current
			::= { hmWanMbusBF 79 }

hmWanMbusBFVIF25		OBJECT-TYPE
			SYNTAX	INTEGER
			MAX-ACCESS	read-only
			STATUS	current
			::= { hmWanMbusBF 80 }

hmWanMbusBFValue25		OBJECT-TYPE
			SYNTAX	INTEGER
			MAX-ACCESS	read-only
			STATUS	current
			::= { hmWanMbusBF 81 }

hmWanMbusBFVIF26		OBJECT-TYPE
			SYNTAX	INTEGER
			MAX-ACCESS	read-only
			STATUS	current
			::= { hmWanMbusBF 82 }

hmWanMbusBFValue26		OBJECT-TYPE
			SYNTAX	INTEGER
			MAX-ACCESS	read-only
			STATUS	current
			::= { hmWanMbusBF 83 }

hmWanMbusBFVIF27		OBJECT-TYPE
			SYNTAX	INTEGER
			MAX-ACCESS	read-only
			STATUS	current
			::= { hmWanMbusBF 84 }

hmWanMbusBFValue27		OBJECT-TYPE
			SYNTAX	INTEGER
			MAX-ACCESS	read-only
			STATUS	current
			::= { hmWanMbusBF 85 }

hmWanMbusBFVIF28		OBJECT-TYPE
			SYNTAX	INTEGER
			MAX-ACCESS	read-only
			STATUS	current
			::= { hmWanMbusBF 86 }

hmWanMbusBFValue28		OBJECT-TYPE
			SYNTAX	INTEGER
			MAX-ACCESS	read-only
			STATUS	current
			::= { hmWanMbusBF 87 }

hmWanMbusBFVIF29		OBJECT-TYPE
			SYNTAX	INTEGER
			MAX-ACCESS	read-only
			STATUS	current
			::= { hmWanMbusBF 88 }

hmWanMbusBFValue29		OBJECT-TYPE
			SYNTAX	INTEGER
			MAX-ACCESS	read-only
			STATUS	current
			::= { hmWanMbusBF 89 }

hmWanMbusBFVIF2A		OBJECT-TYPE
			SYNTAX	INTEGER
			MAX-ACCESS	read-only
			STATUS	current
			::= { hmWanMbusBF 90 }

hmWanMbusBFValue2A		OBJECT-TYPE
			SYNTAX	INTEGER
			MAX-ACCESS	read-only
			STATUS	current
			::= { hmWanMbusBF 91 }

hmWanMbusBFVIF2B		OBJECT-TYPE
			SYNTAX	INTEGER
			MAX-ACCESS	read-only
			STATUS	current
			::= { hmWanMbusBF 92 }

hmWanMbusBFValue2B		OBJECT-TYPE
			SYNTAX	INTEGER
			MAX-ACCESS	read-only
			STATUS	current
			::= { hmWanMbusBF 93 }

hmWanMbusBFVIF2C		OBJECT-TYPE
			SYNTAX	INTEGER
			MAX-ACCESS	read-only
			STATUS	current
			::= { hmWanMbusBF 94 }

hmWanMbusBFValue2C		OBJECT-TYPE
			SYNTAX	INTEGER
			MAX-ACCESS	read-only
			STATUS	current
			::= { hmWanMbusBF 95 }

hmWanMbusBFVIF2D		OBJECT-TYPE
			SYNTAX	INTEGER
			MAX-ACCESS	read-only
			STATUS	current
			::= { hmWanMbusBF 96 }

hmWanMbusBFValue2D		OBJECT-TYPE
			SYNTAX	INTEGER
			MAX-ACCESS	read-only
			STATUS	current
			::= { hmWanMbusBF 97 }

hmWanMbusBFVIF2E		OBJECT-TYPE
			SYNTAX	INTEGER
			MAX-ACCESS	read-only
			STATUS	current
			::= { hmWanMbusBF 98 }

hmWanMbusBFValue2E		OBJECT-TYPE
			SYNTAX	INTEGER
			MAX-ACCESS	read-only
			STATUS	current
			::= { hmWanMbusBF 99 }

hmWanMbusBFVIF2F		OBJECT-TYPE
			SYNTAX	INTEGER
			MAX-ACCESS	read-only
			STATUS	current
			::= { hmWanMbusBF 100 }

hmWanMbusBFValue2F		OBJECT-TYPE
			SYNTAX	INTEGER
			MAX-ACCESS	read-only
			STATUS	current
			::= { hmWanMbusBF 101 }

hmWanMbusC0			OBJECT IDENTIFIER ::= { hmWanMbus 192 }

hmWanMbusC0IdNumber		OBJECT-TYPE
			SYNTAX	Gauge32
			MAX-ACCESS	read-only
			STATUS	current
			::= { hmWanMbusC0 1 }

hmWanMbusC0Manufacturer	OBJECT-TYPE
			SYNTAX	Gauge32
			MAX-ACCESS	read-only
			STATUS	current
			::= { hmWanMbusC0 2 }

hmWanMbusC0Version		OBJECT-TYPE
			SYNTAX	Gauge32
			MAX-ACCESS	read-only
			STATUS	current
			::= { hmWanMbusC0 3 }

hmWanMbusC0Medium		OBJECT-TYPE
			SYNTAX	Gauge32
			MAX-ACCESS	read-only
			STATUS	current
			::= { hmWanMbusC0 4 }

hmWanMbusC0Status		OBJECT-TYPE
			SYNTAX	Gauge32
			MAX-ACCESS	read-only
			STATUS	current
			::= { hmWanMbusC0 5 }

hmWanMbusC0VIF00		OBJECT-TYPE
			SYNTAX	INTEGER
			MAX-ACCESS	read-only
			STATUS	current
			::= { hmWanMbusC0 6 }

hmWanMbusC0Value00		OBJECT-TYPE
			SYNTAX	INTEGER
			MAX-ACCESS	read-only
			STATUS	current
			::= { hmWanMbusC0 7 }

hmWanMbusC0VIF01		OBJECT-TYPE
			SYNTAX	INTEGER
			MAX-ACCESS	read-only
			STATUS	current
			::= { hmWanMbusC0 8 }

hmWanMbusC0Value01		OBJECT-TYPE
			SYNTAX	INTEGER
			MAX-ACCESS	read-only
			STATUS	current
			::= { hmWanMbusC0 9 }

hmWanMbusC0VIF02		OBJECT-TYPE
			SYNTAX	INTEGER
			MAX-ACCESS	read-only
			STATUS	current
			::= { hmWanMbusC0 10 }

hmWanMbusC0Value02		OBJECT-TYPE
			SYNTAX	INTEGER
			MAX-ACCESS	read-only
			STATUS	current
			::= { hmWanMbusC0 11 }

hmWanMbusC0VIF03		OBJECT-TYPE
			SYNTAX	INTEGER
			MAX-ACCESS	read-only
			STATUS	current
			::= { hmWanMbusC0 12 }

hmWanMbusC0Value03		OBJECT-TYPE
			SYNTAX	INTEGER
			MAX-ACCESS	read-only
			STATUS	current
			::= { hmWanMbusC0 13 }

hmWanMbusC0VIF04		OBJECT-TYPE
			SYNTAX	INTEGER
			MAX-ACCESS	read-only
			STATUS	current
			::= { hmWanMbusC0 14 }

hmWanMbusC0Value04		OBJECT-TYPE
			SYNTAX	INTEGER
			MAX-ACCESS	read-only
			STATUS	current
			::= { hmWanMbusC0 15 }

hmWanMbusC0VIF05		OBJECT-TYPE
			SYNTAX	INTEGER
			MAX-ACCESS	read-only
			STATUS	current
			::= { hmWanMbusC0 16 }

hmWanMbusC0Value05		OBJECT-TYPE
			SYNTAX	INTEGER
			MAX-ACCESS	read-only
			STATUS	current
			::= { hmWanMbusC0 17 }

hmWanMbusC0VIF06		OBJECT-TYPE
			SYNTAX	INTEGER
			MAX-ACCESS	read-only
			STATUS	current
			::= { hmWanMbusC0 18 }

hmWanMbusC0Value06		OBJECT-TYPE
			SYNTAX	INTEGER
			MAX-ACCESS	read-only
			STATUS	current
			::= { hmWanMbusC0 19 }

hmWanMbusC0VIF07		OBJECT-TYPE
			SYNTAX	INTEGER
			MAX-ACCESS	read-only
			STATUS	current
			::= { hmWanMbusC0 20 }

hmWanMbusC0Value07		OBJECT-TYPE
			SYNTAX	INTEGER
			MAX-ACCESS	read-only
			STATUS	current
			::= { hmWanMbusC0 21 }

hmWanMbusC0VIF08		OBJECT-TYPE
			SYNTAX	INTEGER
			MAX-ACCESS	read-only
			STATUS	current
			::= { hmWanMbusC0 22 }

hmWanMbusC0Value08		OBJECT-TYPE
			SYNTAX	INTEGER
			MAX-ACCESS	read-only
			STATUS	current
			::= { hmWanMbusC0 23 }

hmWanMbusC0VIF09		OBJECT-TYPE
			SYNTAX	INTEGER
			MAX-ACCESS	read-only
			STATUS	current
			::= { hmWanMbusC0 24 }

hmWanMbusC0Value09		OBJECT-TYPE
			SYNTAX	INTEGER
			MAX-ACCESS	read-only
			STATUS	current
			::= { hmWanMbusC0 25 }

hmWanMbusC0VIF0A		OBJECT-TYPE
			SYNTAX	INTEGER
			MAX-ACCESS	read-only
			STATUS	current
			::= { hmWanMbusC0 26 }

hmWanMbusC0Value0A		OBJECT-TYPE
			SYNTAX	INTEGER
			MAX-ACCESS	read-only
			STATUS	current
			::= { hmWanMbusC0 27 }

hmWanMbusC0VIF0B		OBJECT-TYPE
			SYNTAX	INTEGER
			MAX-ACCESS	read-only
			STATUS	current
			::= { hmWanMbusC0 28 }

hmWanMbusC0Value0B		OBJECT-TYPE
			SYNTAX	INTEGER
			MAX-ACCESS	read-only
			STATUS	current
			::= { hmWanMbusC0 29 }

hmWanMbusC0VIF0C		OBJECT-TYPE
			SYNTAX	INTEGER
			MAX-ACCESS	read-only
			STATUS	current
			::= { hmWanMbusC0 30 }

hmWanMbusC0Value0C		OBJECT-TYPE
			SYNTAX	INTEGER
			MAX-ACCESS	read-only
			STATUS	current
			::= { hmWanMbusC0 31 }

hmWanMbusC0VIF0D		OBJECT-TYPE
			SYNTAX	INTEGER
			MAX-ACCESS	read-only
			STATUS	current
			::= { hmWanMbusC0 32 }

hmWanMbusC0Value0D		OBJECT-TYPE
			SYNTAX	INTEGER
			MAX-ACCESS	read-only
			STATUS	current
			::= { hmWanMbusC0 33 }

hmWanMbusC0VIF0E		OBJECT-TYPE
			SYNTAX	INTEGER
			MAX-ACCESS	read-only
			STATUS	current
			::= { hmWanMbusC0 34 }

hmWanMbusC0Value0E		OBJECT-TYPE
			SYNTAX	INTEGER
			MAX-ACCESS	read-only
			STATUS	current
			::= { hmWanMbusC0 35 }

hmWanMbusC0VIF0F		OBJECT-TYPE
			SYNTAX	INTEGER
			MAX-ACCESS	read-only
			STATUS	current
			::= { hmWanMbusC0 36 }

hmWanMbusC0Value0F		OBJECT-TYPE
			SYNTAX	INTEGER
			MAX-ACCESS	read-only
			STATUS	current
			::= { hmWanMbusC0 37 }

hmWanMbusC0VIF10		OBJECT-TYPE
			SYNTAX	INTEGER
			MAX-ACCESS	read-only
			STATUS	current
			::= { hmWanMbusC0 38 }

hmWanMbusC0Value10		OBJECT-TYPE
			SYNTAX	INTEGER
			MAX-ACCESS	read-only
			STATUS	current
			::= { hmWanMbusC0 39 }

hmWanMbusC0VIF11		OBJECT-TYPE
			SYNTAX	INTEGER
			MAX-ACCESS	read-only
			STATUS	current
			::= { hmWanMbusC0 40 }

hmWanMbusC0Value11		OBJECT-TYPE
			SYNTAX	INTEGER
			MAX-ACCESS	read-only
			STATUS	current
			::= { hmWanMbusC0 41 }

hmWanMbusC0VIF12		OBJECT-TYPE
			SYNTAX	INTEGER
			MAX-ACCESS	read-only
			STATUS	current
			::= { hmWanMbusC0 42 }

hmWanMbusC0Value12		OBJECT-TYPE
			SYNTAX	INTEGER
			MAX-ACCESS	read-only
			STATUS	current
			::= { hmWanMbusC0 43 }

hmWanMbusC0VIF13		OBJECT-TYPE
			SYNTAX	INTEGER
			MAX-ACCESS	read-only
			STATUS	current
			::= { hmWanMbusC0 44 }

hmWanMbusC0Value13		OBJECT-TYPE
			SYNTAX	INTEGER
			MAX-ACCESS	read-only
			STATUS	current
			::= { hmWanMbusC0 45 }

hmWanMbusC0VIF14		OBJECT-TYPE
			SYNTAX	INTEGER
			MAX-ACCESS	read-only
			STATUS	current
			::= { hmWanMbusC0 46 }

hmWanMbusC0Value14		OBJECT-TYPE
			SYNTAX	INTEGER
			MAX-ACCESS	read-only
			STATUS	current
			::= { hmWanMbusC0 47 }

hmWanMbusC0VIF15		OBJECT-TYPE
			SYNTAX	INTEGER
			MAX-ACCESS	read-only
			STATUS	current
			::= { hmWanMbusC0 48 }

hmWanMbusC0Value15		OBJECT-TYPE
			SYNTAX	INTEGER
			MAX-ACCESS	read-only
			STATUS	current
			::= { hmWanMbusC0 49 }

hmWanMbusC0VIF16		OBJECT-TYPE
			SYNTAX	INTEGER
			MAX-ACCESS	read-only
			STATUS	current
			::= { hmWanMbusC0 50 }

hmWanMbusC0Value16		OBJECT-TYPE
			SYNTAX	INTEGER
			MAX-ACCESS	read-only
			STATUS	current
			::= { hmWanMbusC0 51 }

hmWanMbusC0VIF17		OBJECT-TYPE
			SYNTAX	INTEGER
			MAX-ACCESS	read-only
			STATUS	current
			::= { hmWanMbusC0 52 }

hmWanMbusC0Value17		OBJECT-TYPE
			SYNTAX	INTEGER
			MAX-ACCESS	read-only
			STATUS	current
			::= { hmWanMbusC0 53 }

hmWanMbusC0VIF18		OBJECT-TYPE
			SYNTAX	INTEGER
			MAX-ACCESS	read-only
			STATUS	current
			::= { hmWanMbusC0 54 }

hmWanMbusC0Value18		OBJECT-TYPE
			SYNTAX	INTEGER
			MAX-ACCESS	read-only
			STATUS	current
			::= { hmWanMbusC0 55 }

hmWanMbusC0VIF19		OBJECT-TYPE
			SYNTAX	INTEGER
			MAX-ACCESS	read-only
			STATUS	current
			::= { hmWanMbusC0 56 }

hmWanMbusC0Value19		OBJECT-TYPE
			SYNTAX	INTEGER
			MAX-ACCESS	read-only
			STATUS	current
			::= { hmWanMbusC0 57 }

hmWanMbusC0VIF1A		OBJECT-TYPE
			SYNTAX	INTEGER
			MAX-ACCESS	read-only
			STATUS	current
			::= { hmWanMbusC0 58 }

hmWanMbusC0Value1A		OBJECT-TYPE
			SYNTAX	INTEGER
			MAX-ACCESS	read-only
			STATUS	current
			::= { hmWanMbusC0 59 }

hmWanMbusC0VIF1B		OBJECT-TYPE
			SYNTAX	INTEGER
			MAX-ACCESS	read-only
			STATUS	current
			::= { hmWanMbusC0 60 }

hmWanMbusC0Value1B		OBJECT-TYPE
			SYNTAX	INTEGER
			MAX-ACCESS	read-only
			STATUS	current
			::= { hmWanMbusC0 61 }

hmWanMbusC0VIF1C		OBJECT-TYPE
			SYNTAX	INTEGER
			MAX-ACCESS	read-only
			STATUS	current
			::= { hmWanMbusC0 62 }

hmWanMbusC0Value1C		OBJECT-TYPE
			SYNTAX	INTEGER
			MAX-ACCESS	read-only
			STATUS	current
			::= { hmWanMbusC0 63 }

hmWanMbusC0VIF1D		OBJECT-TYPE
			SYNTAX	INTEGER
			MAX-ACCESS	read-only
			STATUS	current
			::= { hmWanMbusC0 64 }

hmWanMbusC0Value1D		OBJECT-TYPE
			SYNTAX	INTEGER
			MAX-ACCESS	read-only
			STATUS	current
			::= { hmWanMbusC0 65 }

hmWanMbusC0VIF1E		OBJECT-TYPE
			SYNTAX	INTEGER
			MAX-ACCESS	read-only
			STATUS	current
			::= { hmWanMbusC0 66 }

hmWanMbusC0Value1E		OBJECT-TYPE
			SYNTAX	INTEGER
			MAX-ACCESS	read-only
			STATUS	current
			::= { hmWanMbusC0 67 }

hmWanMbusC0VIF1F		OBJECT-TYPE
			SYNTAX	INTEGER
			MAX-ACCESS	read-only
			STATUS	current
			::= { hmWanMbusC0 68 }

hmWanMbusC0Value1F		OBJECT-TYPE
			SYNTAX	INTEGER
			MAX-ACCESS	read-only
			STATUS	current
			::= { hmWanMbusC0 69 }

hmWanMbusC0VIF20		OBJECT-TYPE
			SYNTAX	INTEGER
			MAX-ACCESS	read-only
			STATUS	current
			::= { hmWanMbusC0 70 }

hmWanMbusC0Value20		OBJECT-TYPE
			SYNTAX	INTEGER
			MAX-ACCESS	read-only
			STATUS	current
			::= { hmWanMbusC0 71 }

hmWanMbusC0VIF21		OBJECT-TYPE
			SYNTAX	INTEGER
			MAX-ACCESS	read-only
			STATUS	current
			::= { hmWanMbusC0 72 }

hmWanMbusC0Value21		OBJECT-TYPE
			SYNTAX	INTEGER
			MAX-ACCESS	read-only
			STATUS	current
			::= { hmWanMbusC0 73 }

hmWanMbusC0VIF22		OBJECT-TYPE
			SYNTAX	INTEGER
			MAX-ACCESS	read-only
			STATUS	current
			::= { hmWanMbusC0 74 }

hmWanMbusC0Value22		OBJECT-TYPE
			SYNTAX	INTEGER
			MAX-ACCESS	read-only
			STATUS	current
			::= { hmWanMbusC0 75 }

hmWanMbusC0VIF23		OBJECT-TYPE
			SYNTAX	INTEGER
			MAX-ACCESS	read-only
			STATUS	current
			::= { hmWanMbusC0 76 }

hmWanMbusC0Value23		OBJECT-TYPE
			SYNTAX	INTEGER
			MAX-ACCESS	read-only
			STATUS	current
			::= { hmWanMbusC0 77 }

hmWanMbusC0VIF24		OBJECT-TYPE
			SYNTAX	INTEGER
			MAX-ACCESS	read-only
			STATUS	current
			::= { hmWanMbusC0 78 }

hmWanMbusC0Value24		OBJECT-TYPE
			SYNTAX	INTEGER
			MAX-ACCESS	read-only
			STATUS	current
			::= { hmWanMbusC0 79 }

hmWanMbusC0VIF25		OBJECT-TYPE
			SYNTAX	INTEGER
			MAX-ACCESS	read-only
			STATUS	current
			::= { hmWanMbusC0 80 }

hmWanMbusC0Value25		OBJECT-TYPE
			SYNTAX	INTEGER
			MAX-ACCESS	read-only
			STATUS	current
			::= { hmWanMbusC0 81 }

hmWanMbusC0VIF26		OBJECT-TYPE
			SYNTAX	INTEGER
			MAX-ACCESS	read-only
			STATUS	current
			::= { hmWanMbusC0 82 }

hmWanMbusC0Value26		OBJECT-TYPE
			SYNTAX	INTEGER
			MAX-ACCESS	read-only
			STATUS	current
			::= { hmWanMbusC0 83 }

hmWanMbusC0VIF27		OBJECT-TYPE
			SYNTAX	INTEGER
			MAX-ACCESS	read-only
			STATUS	current
			::= { hmWanMbusC0 84 }

hmWanMbusC0Value27		OBJECT-TYPE
			SYNTAX	INTEGER
			MAX-ACCESS	read-only
			STATUS	current
			::= { hmWanMbusC0 85 }

hmWanMbusC0VIF28		OBJECT-TYPE
			SYNTAX	INTEGER
			MAX-ACCESS	read-only
			STATUS	current
			::= { hmWanMbusC0 86 }

hmWanMbusC0Value28		OBJECT-TYPE
			SYNTAX	INTEGER
			MAX-ACCESS	read-only
			STATUS	current
			::= { hmWanMbusC0 87 }

hmWanMbusC0VIF29		OBJECT-TYPE
			SYNTAX	INTEGER
			MAX-ACCESS	read-only
			STATUS	current
			::= { hmWanMbusC0 88 }

hmWanMbusC0Value29		OBJECT-TYPE
			SYNTAX	INTEGER
			MAX-ACCESS	read-only
			STATUS	current
			::= { hmWanMbusC0 89 }

hmWanMbusC0VIF2A		OBJECT-TYPE
			SYNTAX	INTEGER
			MAX-ACCESS	read-only
			STATUS	current
			::= { hmWanMbusC0 90 }

hmWanMbusC0Value2A		OBJECT-TYPE
			SYNTAX	INTEGER
			MAX-ACCESS	read-only
			STATUS	current
			::= { hmWanMbusC0 91 }

hmWanMbusC0VIF2B		OBJECT-TYPE
			SYNTAX	INTEGER
			MAX-ACCESS	read-only
			STATUS	current
			::= { hmWanMbusC0 92 }

hmWanMbusC0Value2B		OBJECT-TYPE
			SYNTAX	INTEGER
			MAX-ACCESS	read-only
			STATUS	current
			::= { hmWanMbusC0 93 }

hmWanMbusC0VIF2C		OBJECT-TYPE
			SYNTAX	INTEGER
			MAX-ACCESS	read-only
			STATUS	current
			::= { hmWanMbusC0 94 }

hmWanMbusC0Value2C		OBJECT-TYPE
			SYNTAX	INTEGER
			MAX-ACCESS	read-only
			STATUS	current
			::= { hmWanMbusC0 95 }

hmWanMbusC0VIF2D		OBJECT-TYPE
			SYNTAX	INTEGER
			MAX-ACCESS	read-only
			STATUS	current
			::= { hmWanMbusC0 96 }

hmWanMbusC0Value2D		OBJECT-TYPE
			SYNTAX	INTEGER
			MAX-ACCESS	read-only
			STATUS	current
			::= { hmWanMbusC0 97 }

hmWanMbusC0VIF2E		OBJECT-TYPE
			SYNTAX	INTEGER
			MAX-ACCESS	read-only
			STATUS	current
			::= { hmWanMbusC0 98 }

hmWanMbusC0Value2E		OBJECT-TYPE
			SYNTAX	INTEGER
			MAX-ACCESS	read-only
			STATUS	current
			::= { hmWanMbusC0 99 }

hmWanMbusC0VIF2F		OBJECT-TYPE
			SYNTAX	INTEGER
			MAX-ACCESS	read-only
			STATUS	current
			::= { hmWanMbusC0 100 }

hmWanMbusC0Value2F		OBJECT-TYPE
			SYNTAX	INTEGER
			MAX-ACCESS	read-only
			STATUS	current
			::= { hmWanMbusC0 101 }

hmWanMbusC1			OBJECT IDENTIFIER ::= { hmWanMbus 193 }

hmWanMbusC1IdNumber		OBJECT-TYPE
			SYNTAX	Gauge32
			MAX-ACCESS	read-only
			STATUS	current
			::= { hmWanMbusC1 1 }

hmWanMbusC1Manufacturer	OBJECT-TYPE
			SYNTAX	Gauge32
			MAX-ACCESS	read-only
			STATUS	current
			::= { hmWanMbusC1 2 }

hmWanMbusC1Version		OBJECT-TYPE
			SYNTAX	Gauge32
			MAX-ACCESS	read-only
			STATUS	current
			::= { hmWanMbusC1 3 }

hmWanMbusC1Medium		OBJECT-TYPE
			SYNTAX	Gauge32
			MAX-ACCESS	read-only
			STATUS	current
			::= { hmWanMbusC1 4 }

hmWanMbusC1Status		OBJECT-TYPE
			SYNTAX	Gauge32
			MAX-ACCESS	read-only
			STATUS	current
			::= { hmWanMbusC1 5 }

hmWanMbusC1VIF00		OBJECT-TYPE
			SYNTAX	INTEGER
			MAX-ACCESS	read-only
			STATUS	current
			::= { hmWanMbusC1 6 }

hmWanMbusC1Value00		OBJECT-TYPE
			SYNTAX	INTEGER
			MAX-ACCESS	read-only
			STATUS	current
			::= { hmWanMbusC1 7 }

hmWanMbusC1VIF01		OBJECT-TYPE
			SYNTAX	INTEGER
			MAX-ACCESS	read-only
			STATUS	current
			::= { hmWanMbusC1 8 }

hmWanMbusC1Value01		OBJECT-TYPE
			SYNTAX	INTEGER
			MAX-ACCESS	read-only
			STATUS	current
			::= { hmWanMbusC1 9 }

hmWanMbusC1VIF02		OBJECT-TYPE
			SYNTAX	INTEGER
			MAX-ACCESS	read-only
			STATUS	current
			::= { hmWanMbusC1 10 }

hmWanMbusC1Value02		OBJECT-TYPE
			SYNTAX	INTEGER
			MAX-ACCESS	read-only
			STATUS	current
			::= { hmWanMbusC1 11 }

hmWanMbusC1VIF03		OBJECT-TYPE
			SYNTAX	INTEGER
			MAX-ACCESS	read-only
			STATUS	current
			::= { hmWanMbusC1 12 }

hmWanMbusC1Value03		OBJECT-TYPE
			SYNTAX	INTEGER
			MAX-ACCESS	read-only
			STATUS	current
			::= { hmWanMbusC1 13 }

hmWanMbusC1VIF04		OBJECT-TYPE
			SYNTAX	INTEGER
			MAX-ACCESS	read-only
			STATUS	current
			::= { hmWanMbusC1 14 }

hmWanMbusC1Value04		OBJECT-TYPE
			SYNTAX	INTEGER
			MAX-ACCESS	read-only
			STATUS	current
			::= { hmWanMbusC1 15 }

hmWanMbusC1VIF05		OBJECT-TYPE
			SYNTAX	INTEGER
			MAX-ACCESS	read-only
			STATUS	current
			::= { hmWanMbusC1 16 }

hmWanMbusC1Value05		OBJECT-TYPE
			SYNTAX	INTEGER
			MAX-ACCESS	read-only
			STATUS	current
			::= { hmWanMbusC1 17 }

hmWanMbusC1VIF06		OBJECT-TYPE
			SYNTAX	INTEGER
			MAX-ACCESS	read-only
			STATUS	current
			::= { hmWanMbusC1 18 }

hmWanMbusC1Value06		OBJECT-TYPE
			SYNTAX	INTEGER
			MAX-ACCESS	read-only
			STATUS	current
			::= { hmWanMbusC1 19 }

hmWanMbusC1VIF07		OBJECT-TYPE
			SYNTAX	INTEGER
			MAX-ACCESS	read-only
			STATUS	current
			::= { hmWanMbusC1 20 }

hmWanMbusC1Value07		OBJECT-TYPE
			SYNTAX	INTEGER
			MAX-ACCESS	read-only
			STATUS	current
			::= { hmWanMbusC1 21 }

hmWanMbusC1VIF08		OBJECT-TYPE
			SYNTAX	INTEGER
			MAX-ACCESS	read-only
			STATUS	current
			::= { hmWanMbusC1 22 }

hmWanMbusC1Value08		OBJECT-TYPE
			SYNTAX	INTEGER
			MAX-ACCESS	read-only
			STATUS	current
			::= { hmWanMbusC1 23 }

hmWanMbusC1VIF09		OBJECT-TYPE
			SYNTAX	INTEGER
			MAX-ACCESS	read-only
			STATUS	current
			::= { hmWanMbusC1 24 }

hmWanMbusC1Value09		OBJECT-TYPE
			SYNTAX	INTEGER
			MAX-ACCESS	read-only
			STATUS	current
			::= { hmWanMbusC1 25 }

hmWanMbusC1VIF0A		OBJECT-TYPE
			SYNTAX	INTEGER
			MAX-ACCESS	read-only
			STATUS	current
			::= { hmWanMbusC1 26 }

hmWanMbusC1Value0A		OBJECT-TYPE
			SYNTAX	INTEGER
			MAX-ACCESS	read-only
			STATUS	current
			::= { hmWanMbusC1 27 }

hmWanMbusC1VIF0B		OBJECT-TYPE
			SYNTAX	INTEGER
			MAX-ACCESS	read-only
			STATUS	current
			::= { hmWanMbusC1 28 }

hmWanMbusC1Value0B		OBJECT-TYPE
			SYNTAX	INTEGER
			MAX-ACCESS	read-only
			STATUS	current
			::= { hmWanMbusC1 29 }

hmWanMbusC1VIF0C		OBJECT-TYPE
			SYNTAX	INTEGER
			MAX-ACCESS	read-only
			STATUS	current
			::= { hmWanMbusC1 30 }

hmWanMbusC1Value0C		OBJECT-TYPE
			SYNTAX	INTEGER
			MAX-ACCESS	read-only
			STATUS	current
			::= { hmWanMbusC1 31 }

hmWanMbusC1VIF0D		OBJECT-TYPE
			SYNTAX	INTEGER
			MAX-ACCESS	read-only
			STATUS	current
			::= { hmWanMbusC1 32 }

hmWanMbusC1Value0D		OBJECT-TYPE
			SYNTAX	INTEGER
			MAX-ACCESS	read-only
			STATUS	current
			::= { hmWanMbusC1 33 }

hmWanMbusC1VIF0E		OBJECT-TYPE
			SYNTAX	INTEGER
			MAX-ACCESS	read-only
			STATUS	current
			::= { hmWanMbusC1 34 }

hmWanMbusC1Value0E		OBJECT-TYPE
			SYNTAX	INTEGER
			MAX-ACCESS	read-only
			STATUS	current
			::= { hmWanMbusC1 35 }

hmWanMbusC1VIF0F		OBJECT-TYPE
			SYNTAX	INTEGER
			MAX-ACCESS	read-only
			STATUS	current
			::= { hmWanMbusC1 36 }

hmWanMbusC1Value0F		OBJECT-TYPE
			SYNTAX	INTEGER
			MAX-ACCESS	read-only
			STATUS	current
			::= { hmWanMbusC1 37 }

hmWanMbusC1VIF10		OBJECT-TYPE
			SYNTAX	INTEGER
			MAX-ACCESS	read-only
			STATUS	current
			::= { hmWanMbusC1 38 }

hmWanMbusC1Value10		OBJECT-TYPE
			SYNTAX	INTEGER
			MAX-ACCESS	read-only
			STATUS	current
			::= { hmWanMbusC1 39 }

hmWanMbusC1VIF11		OBJECT-TYPE
			SYNTAX	INTEGER
			MAX-ACCESS	read-only
			STATUS	current
			::= { hmWanMbusC1 40 }

hmWanMbusC1Value11		OBJECT-TYPE
			SYNTAX	INTEGER
			MAX-ACCESS	read-only
			STATUS	current
			::= { hmWanMbusC1 41 }

hmWanMbusC1VIF12		OBJECT-TYPE
			SYNTAX	INTEGER
			MAX-ACCESS	read-only
			STATUS	current
			::= { hmWanMbusC1 42 }

hmWanMbusC1Value12		OBJECT-TYPE
			SYNTAX	INTEGER
			MAX-ACCESS	read-only
			STATUS	current
			::= { hmWanMbusC1 43 }

hmWanMbusC1VIF13		OBJECT-TYPE
			SYNTAX	INTEGER
			MAX-ACCESS	read-only
			STATUS	current
			::= { hmWanMbusC1 44 }

hmWanMbusC1Value13		OBJECT-TYPE
			SYNTAX	INTEGER
			MAX-ACCESS	read-only
			STATUS	current
			::= { hmWanMbusC1 45 }

hmWanMbusC1VIF14		OBJECT-TYPE
			SYNTAX	INTEGER
			MAX-ACCESS	read-only
			STATUS	current
			::= { hmWanMbusC1 46 }

hmWanMbusC1Value14		OBJECT-TYPE
			SYNTAX	INTEGER
			MAX-ACCESS	read-only
			STATUS	current
			::= { hmWanMbusC1 47 }

hmWanMbusC1VIF15		OBJECT-TYPE
			SYNTAX	INTEGER
			MAX-ACCESS	read-only
			STATUS	current
			::= { hmWanMbusC1 48 }

hmWanMbusC1Value15		OBJECT-TYPE
			SYNTAX	INTEGER
			MAX-ACCESS	read-only
			STATUS	current
			::= { hmWanMbusC1 49 }

hmWanMbusC1VIF16		OBJECT-TYPE
			SYNTAX	INTEGER
			MAX-ACCESS	read-only
			STATUS	current
			::= { hmWanMbusC1 50 }

hmWanMbusC1Value16		OBJECT-TYPE
			SYNTAX	INTEGER
			MAX-ACCESS	read-only
			STATUS	current
			::= { hmWanMbusC1 51 }

hmWanMbusC1VIF17		OBJECT-TYPE
			SYNTAX	INTEGER
			MAX-ACCESS	read-only
			STATUS	current
			::= { hmWanMbusC1 52 }

hmWanMbusC1Value17		OBJECT-TYPE
			SYNTAX	INTEGER
			MAX-ACCESS	read-only
			STATUS	current
			::= { hmWanMbusC1 53 }

hmWanMbusC1VIF18		OBJECT-TYPE
			SYNTAX	INTEGER
			MAX-ACCESS	read-only
			STATUS	current
			::= { hmWanMbusC1 54 }

hmWanMbusC1Value18		OBJECT-TYPE
			SYNTAX	INTEGER
			MAX-ACCESS	read-only
			STATUS	current
			::= { hmWanMbusC1 55 }

hmWanMbusC1VIF19		OBJECT-TYPE
			SYNTAX	INTEGER
			MAX-ACCESS	read-only
			STATUS	current
			::= { hmWanMbusC1 56 }

hmWanMbusC1Value19		OBJECT-TYPE
			SYNTAX	INTEGER
			MAX-ACCESS	read-only
			STATUS	current
			::= { hmWanMbusC1 57 }

hmWanMbusC1VIF1A		OBJECT-TYPE
			SYNTAX	INTEGER
			MAX-ACCESS	read-only
			STATUS	current
			::= { hmWanMbusC1 58 }

hmWanMbusC1Value1A		OBJECT-TYPE
			SYNTAX	INTEGER
			MAX-ACCESS	read-only
			STATUS	current
			::= { hmWanMbusC1 59 }

hmWanMbusC1VIF1B		OBJECT-TYPE
			SYNTAX	INTEGER
			MAX-ACCESS	read-only
			STATUS	current
			::= { hmWanMbusC1 60 }

hmWanMbusC1Value1B		OBJECT-TYPE
			SYNTAX	INTEGER
			MAX-ACCESS	read-only
			STATUS	current
			::= { hmWanMbusC1 61 }

hmWanMbusC1VIF1C		OBJECT-TYPE
			SYNTAX	INTEGER
			MAX-ACCESS	read-only
			STATUS	current
			::= { hmWanMbusC1 62 }

hmWanMbusC1Value1C		OBJECT-TYPE
			SYNTAX	INTEGER
			MAX-ACCESS	read-only
			STATUS	current
			::= { hmWanMbusC1 63 }

hmWanMbusC1VIF1D		OBJECT-TYPE
			SYNTAX	INTEGER
			MAX-ACCESS	read-only
			STATUS	current
			::= { hmWanMbusC1 64 }

hmWanMbusC1Value1D		OBJECT-TYPE
			SYNTAX	INTEGER
			MAX-ACCESS	read-only
			STATUS	current
			::= { hmWanMbusC1 65 }

hmWanMbusC1VIF1E		OBJECT-TYPE
			SYNTAX	INTEGER
			MAX-ACCESS	read-only
			STATUS	current
			::= { hmWanMbusC1 66 }

hmWanMbusC1Value1E		OBJECT-TYPE
			SYNTAX	INTEGER
			MAX-ACCESS	read-only
			STATUS	current
			::= { hmWanMbusC1 67 }

hmWanMbusC1VIF1F		OBJECT-TYPE
			SYNTAX	INTEGER
			MAX-ACCESS	read-only
			STATUS	current
			::= { hmWanMbusC1 68 }

hmWanMbusC1Value1F		OBJECT-TYPE
			SYNTAX	INTEGER
			MAX-ACCESS	read-only
			STATUS	current
			::= { hmWanMbusC1 69 }

hmWanMbusC1VIF20		OBJECT-TYPE
			SYNTAX	INTEGER
			MAX-ACCESS	read-only
			STATUS	current
			::= { hmWanMbusC1 70 }

hmWanMbusC1Value20		OBJECT-TYPE
			SYNTAX	INTEGER
			MAX-ACCESS	read-only
			STATUS	current
			::= { hmWanMbusC1 71 }

hmWanMbusC1VIF21		OBJECT-TYPE
			SYNTAX	INTEGER
			MAX-ACCESS	read-only
			STATUS	current
			::= { hmWanMbusC1 72 }

hmWanMbusC1Value21		OBJECT-TYPE
			SYNTAX	INTEGER
			MAX-ACCESS	read-only
			STATUS	current
			::= { hmWanMbusC1 73 }

hmWanMbusC1VIF22		OBJECT-TYPE
			SYNTAX	INTEGER
			MAX-ACCESS	read-only
			STATUS	current
			::= { hmWanMbusC1 74 }

hmWanMbusC1Value22		OBJECT-TYPE
			SYNTAX	INTEGER
			MAX-ACCESS	read-only
			STATUS	current
			::= { hmWanMbusC1 75 }

hmWanMbusC1VIF23		OBJECT-TYPE
			SYNTAX	INTEGER
			MAX-ACCESS	read-only
			STATUS	current
			::= { hmWanMbusC1 76 }

hmWanMbusC1Value23		OBJECT-TYPE
			SYNTAX	INTEGER
			MAX-ACCESS	read-only
			STATUS	current
			::= { hmWanMbusC1 77 }

hmWanMbusC1VIF24		OBJECT-TYPE
			SYNTAX	INTEGER
			MAX-ACCESS	read-only
			STATUS	current
			::= { hmWanMbusC1 78 }

hmWanMbusC1Value24		OBJECT-TYPE
			SYNTAX	INTEGER
			MAX-ACCESS	read-only
			STATUS	current
			::= { hmWanMbusC1 79 }

hmWanMbusC1VIF25		OBJECT-TYPE
			SYNTAX	INTEGER
			MAX-ACCESS	read-only
			STATUS	current
			::= { hmWanMbusC1 80 }

hmWanMbusC1Value25		OBJECT-TYPE
			SYNTAX	INTEGER
			MAX-ACCESS	read-only
			STATUS	current
			::= { hmWanMbusC1 81 }

hmWanMbusC1VIF26		OBJECT-TYPE
			SYNTAX	INTEGER
			MAX-ACCESS	read-only
			STATUS	current
			::= { hmWanMbusC1 82 }

hmWanMbusC1Value26		OBJECT-TYPE
			SYNTAX	INTEGER
			MAX-ACCESS	read-only
			STATUS	current
			::= { hmWanMbusC1 83 }

hmWanMbusC1VIF27		OBJECT-TYPE
			SYNTAX	INTEGER
			MAX-ACCESS	read-only
			STATUS	current
			::= { hmWanMbusC1 84 }

hmWanMbusC1Value27		OBJECT-TYPE
			SYNTAX	INTEGER
			MAX-ACCESS	read-only
			STATUS	current
			::= { hmWanMbusC1 85 }

hmWanMbusC1VIF28		OBJECT-TYPE
			SYNTAX	INTEGER
			MAX-ACCESS	read-only
			STATUS	current
			::= { hmWanMbusC1 86 }

hmWanMbusC1Value28		OBJECT-TYPE
			SYNTAX	INTEGER
			MAX-ACCESS	read-only
			STATUS	current
			::= { hmWanMbusC1 87 }

hmWanMbusC1VIF29		OBJECT-TYPE
			SYNTAX	INTEGER
			MAX-ACCESS	read-only
			STATUS	current
			::= { hmWanMbusC1 88 }

hmWanMbusC1Value29		OBJECT-TYPE
			SYNTAX	INTEGER
			MAX-ACCESS	read-only
			STATUS	current
			::= { hmWanMbusC1 89 }

hmWanMbusC1VIF2A		OBJECT-TYPE
			SYNTAX	INTEGER
			MAX-ACCESS	read-only
			STATUS	current
			::= { hmWanMbusC1 90 }

hmWanMbusC1Value2A		OBJECT-TYPE
			SYNTAX	INTEGER
			MAX-ACCESS	read-only
			STATUS	current
			::= { hmWanMbusC1 91 }

hmWanMbusC1VIF2B		OBJECT-TYPE
			SYNTAX	INTEGER
			MAX-ACCESS	read-only
			STATUS	current
			::= { hmWanMbusC1 92 }

hmWanMbusC1Value2B		OBJECT-TYPE
			SYNTAX	INTEGER
			MAX-ACCESS	read-only
			STATUS	current
			::= { hmWanMbusC1 93 }

hmWanMbusC1VIF2C		OBJECT-TYPE
			SYNTAX	INTEGER
			MAX-ACCESS	read-only
			STATUS	current
			::= { hmWanMbusC1 94 }

hmWanMbusC1Value2C		OBJECT-TYPE
			SYNTAX	INTEGER
			MAX-ACCESS	read-only
			STATUS	current
			::= { hmWanMbusC1 95 }

hmWanMbusC1VIF2D		OBJECT-TYPE
			SYNTAX	INTEGER
			MAX-ACCESS	read-only
			STATUS	current
			::= { hmWanMbusC1 96 }

hmWanMbusC1Value2D		OBJECT-TYPE
			SYNTAX	INTEGER
			MAX-ACCESS	read-only
			STATUS	current
			::= { hmWanMbusC1 97 }

hmWanMbusC1VIF2E		OBJECT-TYPE
			SYNTAX	INTEGER
			MAX-ACCESS	read-only
			STATUS	current
			::= { hmWanMbusC1 98 }

hmWanMbusC1Value2E		OBJECT-TYPE
			SYNTAX	INTEGER
			MAX-ACCESS	read-only
			STATUS	current
			::= { hmWanMbusC1 99 }

hmWanMbusC1VIF2F		OBJECT-TYPE
			SYNTAX	INTEGER
			MAX-ACCESS	read-only
			STATUS	current
			::= { hmWanMbusC1 100 }

hmWanMbusC1Value2F		OBJECT-TYPE
			SYNTAX	INTEGER
			MAX-ACCESS	read-only
			STATUS	current
			::= { hmWanMbusC1 101 }

hmWanMbusC2			OBJECT IDENTIFIER ::= { hmWanMbus 194 }

hmWanMbusC2IdNumber		OBJECT-TYPE
			SYNTAX	Gauge32
			MAX-ACCESS	read-only
			STATUS	current
			::= { hmWanMbusC2 1 }

hmWanMbusC2Manufacturer	OBJECT-TYPE
			SYNTAX	Gauge32
			MAX-ACCESS	read-only
			STATUS	current
			::= { hmWanMbusC2 2 }

hmWanMbusC2Version		OBJECT-TYPE
			SYNTAX	Gauge32
			MAX-ACCESS	read-only
			STATUS	current
			::= { hmWanMbusC2 3 }

hmWanMbusC2Medium		OBJECT-TYPE
			SYNTAX	Gauge32
			MAX-ACCESS	read-only
			STATUS	current
			::= { hmWanMbusC2 4 }

hmWanMbusC2Status		OBJECT-TYPE
			SYNTAX	Gauge32
			MAX-ACCESS	read-only
			STATUS	current
			::= { hmWanMbusC2 5 }

hmWanMbusC2VIF00		OBJECT-TYPE
			SYNTAX	INTEGER
			MAX-ACCESS	read-only
			STATUS	current
			::= { hmWanMbusC2 6 }

hmWanMbusC2Value00		OBJECT-TYPE
			SYNTAX	INTEGER
			MAX-ACCESS	read-only
			STATUS	current
			::= { hmWanMbusC2 7 }

hmWanMbusC2VIF01		OBJECT-TYPE
			SYNTAX	INTEGER
			MAX-ACCESS	read-only
			STATUS	current
			::= { hmWanMbusC2 8 }

hmWanMbusC2Value01		OBJECT-TYPE
			SYNTAX	INTEGER
			MAX-ACCESS	read-only
			STATUS	current
			::= { hmWanMbusC2 9 }

hmWanMbusC2VIF02		OBJECT-TYPE
			SYNTAX	INTEGER
			MAX-ACCESS	read-only
			STATUS	current
			::= { hmWanMbusC2 10 }

hmWanMbusC2Value02		OBJECT-TYPE
			SYNTAX	INTEGER
			MAX-ACCESS	read-only
			STATUS	current
			::= { hmWanMbusC2 11 }

hmWanMbusC2VIF03		OBJECT-TYPE
			SYNTAX	INTEGER
			MAX-ACCESS	read-only
			STATUS	current
			::= { hmWanMbusC2 12 }

hmWanMbusC2Value03		OBJECT-TYPE
			SYNTAX	INTEGER
			MAX-ACCESS	read-only
			STATUS	current
			::= { hmWanMbusC2 13 }

hmWanMbusC2VIF04		OBJECT-TYPE
			SYNTAX	INTEGER
			MAX-ACCESS	read-only
			STATUS	current
			::= { hmWanMbusC2 14 }

hmWanMbusC2Value04		OBJECT-TYPE
			SYNTAX	INTEGER
			MAX-ACCESS	read-only
			STATUS	current
			::= { hmWanMbusC2 15 }

hmWanMbusC2VIF05		OBJECT-TYPE
			SYNTAX	INTEGER
			MAX-ACCESS	read-only
			STATUS	current
			::= { hmWanMbusC2 16 }

hmWanMbusC2Value05		OBJECT-TYPE
			SYNTAX	INTEGER
			MAX-ACCESS	read-only
			STATUS	current
			::= { hmWanMbusC2 17 }

hmWanMbusC2VIF06		OBJECT-TYPE
			SYNTAX	INTEGER
			MAX-ACCESS	read-only
			STATUS	current
			::= { hmWanMbusC2 18 }

hmWanMbusC2Value06		OBJECT-TYPE
			SYNTAX	INTEGER
			MAX-ACCESS	read-only
			STATUS	current
			::= { hmWanMbusC2 19 }

hmWanMbusC2VIF07		OBJECT-TYPE
			SYNTAX	INTEGER
			MAX-ACCESS	read-only
			STATUS	current
			::= { hmWanMbusC2 20 }

hmWanMbusC2Value07		OBJECT-TYPE
			SYNTAX	INTEGER
			MAX-ACCESS	read-only
			STATUS	current
			::= { hmWanMbusC2 21 }

hmWanMbusC2VIF08		OBJECT-TYPE
			SYNTAX	INTEGER
			MAX-ACCESS	read-only
			STATUS	current
			::= { hmWanMbusC2 22 }

hmWanMbusC2Value08		OBJECT-TYPE
			SYNTAX	INTEGER
			MAX-ACCESS	read-only
			STATUS	current
			::= { hmWanMbusC2 23 }

hmWanMbusC2VIF09		OBJECT-TYPE
			SYNTAX	INTEGER
			MAX-ACCESS	read-only
			STATUS	current
			::= { hmWanMbusC2 24 }

hmWanMbusC2Value09		OBJECT-TYPE
			SYNTAX	INTEGER
			MAX-ACCESS	read-only
			STATUS	current
			::= { hmWanMbusC2 25 }

hmWanMbusC2VIF0A		OBJECT-TYPE
			SYNTAX	INTEGER
			MAX-ACCESS	read-only
			STATUS	current
			::= { hmWanMbusC2 26 }

hmWanMbusC2Value0A		OBJECT-TYPE
			SYNTAX	INTEGER
			MAX-ACCESS	read-only
			STATUS	current
			::= { hmWanMbusC2 27 }

hmWanMbusC2VIF0B		OBJECT-TYPE
			SYNTAX	INTEGER
			MAX-ACCESS	read-only
			STATUS	current
			::= { hmWanMbusC2 28 }

hmWanMbusC2Value0B		OBJECT-TYPE
			SYNTAX	INTEGER
			MAX-ACCESS	read-only
			STATUS	current
			::= { hmWanMbusC2 29 }

hmWanMbusC2VIF0C		OBJECT-TYPE
			SYNTAX	INTEGER
			MAX-ACCESS	read-only
			STATUS	current
			::= { hmWanMbusC2 30 }

hmWanMbusC2Value0C		OBJECT-TYPE
			SYNTAX	INTEGER
			MAX-ACCESS	read-only
			STATUS	current
			::= { hmWanMbusC2 31 }

hmWanMbusC2VIF0D		OBJECT-TYPE
			SYNTAX	INTEGER
			MAX-ACCESS	read-only
			STATUS	current
			::= { hmWanMbusC2 32 }

hmWanMbusC2Value0D		OBJECT-TYPE
			SYNTAX	INTEGER
			MAX-ACCESS	read-only
			STATUS	current
			::= { hmWanMbusC2 33 }

hmWanMbusC2VIF0E		OBJECT-TYPE
			SYNTAX	INTEGER
			MAX-ACCESS	read-only
			STATUS	current
			::= { hmWanMbusC2 34 }

hmWanMbusC2Value0E		OBJECT-TYPE
			SYNTAX	INTEGER
			MAX-ACCESS	read-only
			STATUS	current
			::= { hmWanMbusC2 35 }

hmWanMbusC2VIF0F		OBJECT-TYPE
			SYNTAX	INTEGER
			MAX-ACCESS	read-only
			STATUS	current
			::= { hmWanMbusC2 36 }

hmWanMbusC2Value0F		OBJECT-TYPE
			SYNTAX	INTEGER
			MAX-ACCESS	read-only
			STATUS	current
			::= { hmWanMbusC2 37 }

hmWanMbusC2VIF10		OBJECT-TYPE
			SYNTAX	INTEGER
			MAX-ACCESS	read-only
			STATUS	current
			::= { hmWanMbusC2 38 }

hmWanMbusC2Value10		OBJECT-TYPE
			SYNTAX	INTEGER
			MAX-ACCESS	read-only
			STATUS	current
			::= { hmWanMbusC2 39 }

hmWanMbusC2VIF11		OBJECT-TYPE
			SYNTAX	INTEGER
			MAX-ACCESS	read-only
			STATUS	current
			::= { hmWanMbusC2 40 }

hmWanMbusC2Value11		OBJECT-TYPE
			SYNTAX	INTEGER
			MAX-ACCESS	read-only
			STATUS	current
			::= { hmWanMbusC2 41 }

hmWanMbusC2VIF12		OBJECT-TYPE
			SYNTAX	INTEGER
			MAX-ACCESS	read-only
			STATUS	current
			::= { hmWanMbusC2 42 }

hmWanMbusC2Value12		OBJECT-TYPE
			SYNTAX	INTEGER
			MAX-ACCESS	read-only
			STATUS	current
			::= { hmWanMbusC2 43 }

hmWanMbusC2VIF13		OBJECT-TYPE
			SYNTAX	INTEGER
			MAX-ACCESS	read-only
			STATUS	current
			::= { hmWanMbusC2 44 }

hmWanMbusC2Value13		OBJECT-TYPE
			SYNTAX	INTEGER
			MAX-ACCESS	read-only
			STATUS	current
			::= { hmWanMbusC2 45 }

hmWanMbusC2VIF14		OBJECT-TYPE
			SYNTAX	INTEGER
			MAX-ACCESS	read-only
			STATUS	current
			::= { hmWanMbusC2 46 }

hmWanMbusC2Value14		OBJECT-TYPE
			SYNTAX	INTEGER
			MAX-ACCESS	read-only
			STATUS	current
			::= { hmWanMbusC2 47 }

hmWanMbusC2VIF15		OBJECT-TYPE
			SYNTAX	INTEGER
			MAX-ACCESS	read-only
			STATUS	current
			::= { hmWanMbusC2 48 }

hmWanMbusC2Value15		OBJECT-TYPE
			SYNTAX	INTEGER
			MAX-ACCESS	read-only
			STATUS	current
			::= { hmWanMbusC2 49 }

hmWanMbusC2VIF16		OBJECT-TYPE
			SYNTAX	INTEGER
			MAX-ACCESS	read-only
			STATUS	current
			::= { hmWanMbusC2 50 }

hmWanMbusC2Value16		OBJECT-TYPE
			SYNTAX	INTEGER
			MAX-ACCESS	read-only
			STATUS	current
			::= { hmWanMbusC2 51 }

hmWanMbusC2VIF17		OBJECT-TYPE
			SYNTAX	INTEGER
			MAX-ACCESS	read-only
			STATUS	current
			::= { hmWanMbusC2 52 }

hmWanMbusC2Value17		OBJECT-TYPE
			SYNTAX	INTEGER
			MAX-ACCESS	read-only
			STATUS	current
			::= { hmWanMbusC2 53 }

hmWanMbusC2VIF18		OBJECT-TYPE
			SYNTAX	INTEGER
			MAX-ACCESS	read-only
			STATUS	current
			::= { hmWanMbusC2 54 }

hmWanMbusC2Value18		OBJECT-TYPE
			SYNTAX	INTEGER
			MAX-ACCESS	read-only
			STATUS	current
			::= { hmWanMbusC2 55 }

hmWanMbusC2VIF19		OBJECT-TYPE
			SYNTAX	INTEGER
			MAX-ACCESS	read-only
			STATUS	current
			::= { hmWanMbusC2 56 }

hmWanMbusC2Value19		OBJECT-TYPE
			SYNTAX	INTEGER
			MAX-ACCESS	read-only
			STATUS	current
			::= { hmWanMbusC2 57 }

hmWanMbusC2VIF1A		OBJECT-TYPE
			SYNTAX	INTEGER
			MAX-ACCESS	read-only
			STATUS	current
			::= { hmWanMbusC2 58 }

hmWanMbusC2Value1A		OBJECT-TYPE
			SYNTAX	INTEGER
			MAX-ACCESS	read-only
			STATUS	current
			::= { hmWanMbusC2 59 }

hmWanMbusC2VIF1B		OBJECT-TYPE
			SYNTAX	INTEGER
			MAX-ACCESS	read-only
			STATUS	current
			::= { hmWanMbusC2 60 }

hmWanMbusC2Value1B		OBJECT-TYPE
			SYNTAX	INTEGER
			MAX-ACCESS	read-only
			STATUS	current
			::= { hmWanMbusC2 61 }

hmWanMbusC2VIF1C		OBJECT-TYPE
			SYNTAX	INTEGER
			MAX-ACCESS	read-only
			STATUS	current
			::= { hmWanMbusC2 62 }

hmWanMbusC2Value1C		OBJECT-TYPE
			SYNTAX	INTEGER
			MAX-ACCESS	read-only
			STATUS	current
			::= { hmWanMbusC2 63 }

hmWanMbusC2VIF1D		OBJECT-TYPE
			SYNTAX	INTEGER
			MAX-ACCESS	read-only
			STATUS	current
			::= { hmWanMbusC2 64 }

hmWanMbusC2Value1D		OBJECT-TYPE
			SYNTAX	INTEGER
			MAX-ACCESS	read-only
			STATUS	current
			::= { hmWanMbusC2 65 }

hmWanMbusC2VIF1E		OBJECT-TYPE
			SYNTAX	INTEGER
			MAX-ACCESS	read-only
			STATUS	current
			::= { hmWanMbusC2 66 }

hmWanMbusC2Value1E		OBJECT-TYPE
			SYNTAX	INTEGER
			MAX-ACCESS	read-only
			STATUS	current
			::= { hmWanMbusC2 67 }

hmWanMbusC2VIF1F		OBJECT-TYPE
			SYNTAX	INTEGER
			MAX-ACCESS	read-only
			STATUS	current
			::= { hmWanMbusC2 68 }

hmWanMbusC2Value1F		OBJECT-TYPE
			SYNTAX	INTEGER
			MAX-ACCESS	read-only
			STATUS	current
			::= { hmWanMbusC2 69 }

hmWanMbusC2VIF20		OBJECT-TYPE
			SYNTAX	INTEGER
			MAX-ACCESS	read-only
			STATUS	current
			::= { hmWanMbusC2 70 }

hmWanMbusC2Value20		OBJECT-TYPE
			SYNTAX	INTEGER
			MAX-ACCESS	read-only
			STATUS	current
			::= { hmWanMbusC2 71 }

hmWanMbusC2VIF21		OBJECT-TYPE
			SYNTAX	INTEGER
			MAX-ACCESS	read-only
			STATUS	current
			::= { hmWanMbusC2 72 }

hmWanMbusC2Value21		OBJECT-TYPE
			SYNTAX	INTEGER
			MAX-ACCESS	read-only
			STATUS	current
			::= { hmWanMbusC2 73 }

hmWanMbusC2VIF22		OBJECT-TYPE
			SYNTAX	INTEGER
			MAX-ACCESS	read-only
			STATUS	current
			::= { hmWanMbusC2 74 }

hmWanMbusC2Value22		OBJECT-TYPE
			SYNTAX	INTEGER
			MAX-ACCESS	read-only
			STATUS	current
			::= { hmWanMbusC2 75 }

hmWanMbusC2VIF23		OBJECT-TYPE
			SYNTAX	INTEGER
			MAX-ACCESS	read-only
			STATUS	current
			::= { hmWanMbusC2 76 }

hmWanMbusC2Value23		OBJECT-TYPE
			SYNTAX	INTEGER
			MAX-ACCESS	read-only
			STATUS	current
			::= { hmWanMbusC2 77 }

hmWanMbusC2VIF24		OBJECT-TYPE
			SYNTAX	INTEGER
			MAX-ACCESS	read-only
			STATUS	current
			::= { hmWanMbusC2 78 }

hmWanMbusC2Value24		OBJECT-TYPE
			SYNTAX	INTEGER
			MAX-ACCESS	read-only
			STATUS	current
			::= { hmWanMbusC2 79 }

hmWanMbusC2VIF25		OBJECT-TYPE
			SYNTAX	INTEGER
			MAX-ACCESS	read-only
			STATUS	current
			::= { hmWanMbusC2 80 }

hmWanMbusC2Value25		OBJECT-TYPE
			SYNTAX	INTEGER
			MAX-ACCESS	read-only
			STATUS	current
			::= { hmWanMbusC2 81 }

hmWanMbusC2VIF26		OBJECT-TYPE
			SYNTAX	INTEGER
			MAX-ACCESS	read-only
			STATUS	current
			::= { hmWanMbusC2 82 }

hmWanMbusC2Value26		OBJECT-TYPE
			SYNTAX	INTEGER
			MAX-ACCESS	read-only
			STATUS	current
			::= { hmWanMbusC2 83 }

hmWanMbusC2VIF27		OBJECT-TYPE
			SYNTAX	INTEGER
			MAX-ACCESS	read-only
			STATUS	current
			::= { hmWanMbusC2 84 }

hmWanMbusC2Value27		OBJECT-TYPE
			SYNTAX	INTEGER
			MAX-ACCESS	read-only
			STATUS	current
			::= { hmWanMbusC2 85 }

hmWanMbusC2VIF28		OBJECT-TYPE
			SYNTAX	INTEGER
			MAX-ACCESS	read-only
			STATUS	current
			::= { hmWanMbusC2 86 }

hmWanMbusC2Value28		OBJECT-TYPE
			SYNTAX	INTEGER
			MAX-ACCESS	read-only
			STATUS	current
			::= { hmWanMbusC2 87 }

hmWanMbusC2VIF29		OBJECT-TYPE
			SYNTAX	INTEGER
			MAX-ACCESS	read-only
			STATUS	current
			::= { hmWanMbusC2 88 }

hmWanMbusC2Value29		OBJECT-TYPE
			SYNTAX	INTEGER
			MAX-ACCESS	read-only
			STATUS	current
			::= { hmWanMbusC2 89 }

hmWanMbusC2VIF2A		OBJECT-TYPE
			SYNTAX	INTEGER
			MAX-ACCESS	read-only
			STATUS	current
			::= { hmWanMbusC2 90 }

hmWanMbusC2Value2A		OBJECT-TYPE
			SYNTAX	INTEGER
			MAX-ACCESS	read-only
			STATUS	current
			::= { hmWanMbusC2 91 }

hmWanMbusC2VIF2B		OBJECT-TYPE
			SYNTAX	INTEGER
			MAX-ACCESS	read-only
			STATUS	current
			::= { hmWanMbusC2 92 }

hmWanMbusC2Value2B		OBJECT-TYPE
			SYNTAX	INTEGER
			MAX-ACCESS	read-only
			STATUS	current
			::= { hmWanMbusC2 93 }

hmWanMbusC2VIF2C		OBJECT-TYPE
			SYNTAX	INTEGER
			MAX-ACCESS	read-only
			STATUS	current
			::= { hmWanMbusC2 94 }

hmWanMbusC2Value2C		OBJECT-TYPE
			SYNTAX	INTEGER
			MAX-ACCESS	read-only
			STATUS	current
			::= { hmWanMbusC2 95 }

hmWanMbusC2VIF2D		OBJECT-TYPE
			SYNTAX	INTEGER
			MAX-ACCESS	read-only
			STATUS	current
			::= { hmWanMbusC2 96 }

hmWanMbusC2Value2D		OBJECT-TYPE
			SYNTAX	INTEGER
			MAX-ACCESS	read-only
			STATUS	current
			::= { hmWanMbusC2 97 }

hmWanMbusC2VIF2E		OBJECT-TYPE
			SYNTAX	INTEGER
			MAX-ACCESS	read-only
			STATUS	current
			::= { hmWanMbusC2 98 }

hmWanMbusC2Value2E		OBJECT-TYPE
			SYNTAX	INTEGER
			MAX-ACCESS	read-only
			STATUS	current
			::= { hmWanMbusC2 99 }

hmWanMbusC2VIF2F		OBJECT-TYPE
			SYNTAX	INTEGER
			MAX-ACCESS	read-only
			STATUS	current
			::= { hmWanMbusC2 100 }

hmWanMbusC2Value2F		OBJECT-TYPE
			SYNTAX	INTEGER
			MAX-ACCESS	read-only
			STATUS	current
			::= { hmWanMbusC2 101 }

hmWanMbusC3			OBJECT IDENTIFIER ::= { hmWanMbus 195 }

hmWanMbusC3IdNumber		OBJECT-TYPE
			SYNTAX	Gauge32
			MAX-ACCESS	read-only
			STATUS	current
			::= { hmWanMbusC3 1 }

hmWanMbusC3Manufacturer	OBJECT-TYPE
			SYNTAX	Gauge32
			MAX-ACCESS	read-only
			STATUS	current
			::= { hmWanMbusC3 2 }

hmWanMbusC3Version		OBJECT-TYPE
			SYNTAX	Gauge32
			MAX-ACCESS	read-only
			STATUS	current
			::= { hmWanMbusC3 3 }

hmWanMbusC3Medium		OBJECT-TYPE
			SYNTAX	Gauge32
			MAX-ACCESS	read-only
			STATUS	current
			::= { hmWanMbusC3 4 }

hmWanMbusC3Status		OBJECT-TYPE
			SYNTAX	Gauge32
			MAX-ACCESS	read-only
			STATUS	current
			::= { hmWanMbusC3 5 }

hmWanMbusC3VIF00		OBJECT-TYPE
			SYNTAX	INTEGER
			MAX-ACCESS	read-only
			STATUS	current
			::= { hmWanMbusC3 6 }

hmWanMbusC3Value00		OBJECT-TYPE
			SYNTAX	INTEGER
			MAX-ACCESS	read-only
			STATUS	current
			::= { hmWanMbusC3 7 }

hmWanMbusC3VIF01		OBJECT-TYPE
			SYNTAX	INTEGER
			MAX-ACCESS	read-only
			STATUS	current
			::= { hmWanMbusC3 8 }

hmWanMbusC3Value01		OBJECT-TYPE
			SYNTAX	INTEGER
			MAX-ACCESS	read-only
			STATUS	current
			::= { hmWanMbusC3 9 }

hmWanMbusC3VIF02		OBJECT-TYPE
			SYNTAX	INTEGER
			MAX-ACCESS	read-only
			STATUS	current
			::= { hmWanMbusC3 10 }

hmWanMbusC3Value02		OBJECT-TYPE
			SYNTAX	INTEGER
			MAX-ACCESS	read-only
			STATUS	current
			::= { hmWanMbusC3 11 }

hmWanMbusC3VIF03		OBJECT-TYPE
			SYNTAX	INTEGER
			MAX-ACCESS	read-only
			STATUS	current
			::= { hmWanMbusC3 12 }

hmWanMbusC3Value03		OBJECT-TYPE
			SYNTAX	INTEGER
			MAX-ACCESS	read-only
			STATUS	current
			::= { hmWanMbusC3 13 }

hmWanMbusC3VIF04		OBJECT-TYPE
			SYNTAX	INTEGER
			MAX-ACCESS	read-only
			STATUS	current
			::= { hmWanMbusC3 14 }

hmWanMbusC3Value04		OBJECT-TYPE
			SYNTAX	INTEGER
			MAX-ACCESS	read-only
			STATUS	current
			::= { hmWanMbusC3 15 }

hmWanMbusC3VIF05		OBJECT-TYPE
			SYNTAX	INTEGER
			MAX-ACCESS	read-only
			STATUS	current
			::= { hmWanMbusC3 16 }

hmWanMbusC3Value05		OBJECT-TYPE
			SYNTAX	INTEGER
			MAX-ACCESS	read-only
			STATUS	current
			::= { hmWanMbusC3 17 }

hmWanMbusC3VIF06		OBJECT-TYPE
			SYNTAX	INTEGER
			MAX-ACCESS	read-only
			STATUS	current
			::= { hmWanMbusC3 18 }

hmWanMbusC3Value06		OBJECT-TYPE
			SYNTAX	INTEGER
			MAX-ACCESS	read-only
			STATUS	current
			::= { hmWanMbusC3 19 }

hmWanMbusC3VIF07		OBJECT-TYPE
			SYNTAX	INTEGER
			MAX-ACCESS	read-only
			STATUS	current
			::= { hmWanMbusC3 20 }

hmWanMbusC3Value07		OBJECT-TYPE
			SYNTAX	INTEGER
			MAX-ACCESS	read-only
			STATUS	current
			::= { hmWanMbusC3 21 }

hmWanMbusC3VIF08		OBJECT-TYPE
			SYNTAX	INTEGER
			MAX-ACCESS	read-only
			STATUS	current
			::= { hmWanMbusC3 22 }

hmWanMbusC3Value08		OBJECT-TYPE
			SYNTAX	INTEGER
			MAX-ACCESS	read-only
			STATUS	current
			::= { hmWanMbusC3 23 }

hmWanMbusC3VIF09		OBJECT-TYPE
			SYNTAX	INTEGER
			MAX-ACCESS	read-only
			STATUS	current
			::= { hmWanMbusC3 24 }

hmWanMbusC3Value09		OBJECT-TYPE
			SYNTAX	INTEGER
			MAX-ACCESS	read-only
			STATUS	current
			::= { hmWanMbusC3 25 }

hmWanMbusC3VIF0A		OBJECT-TYPE
			SYNTAX	INTEGER
			MAX-ACCESS	read-only
			STATUS	current
			::= { hmWanMbusC3 26 }

hmWanMbusC3Value0A		OBJECT-TYPE
			SYNTAX	INTEGER
			MAX-ACCESS	read-only
			STATUS	current
			::= { hmWanMbusC3 27 }

hmWanMbusC3VIF0B		OBJECT-TYPE
			SYNTAX	INTEGER
			MAX-ACCESS	read-only
			STATUS	current
			::= { hmWanMbusC3 28 }

hmWanMbusC3Value0B		OBJECT-TYPE
			SYNTAX	INTEGER
			MAX-ACCESS	read-only
			STATUS	current
			::= { hmWanMbusC3 29 }

hmWanMbusC3VIF0C		OBJECT-TYPE
			SYNTAX	INTEGER
			MAX-ACCESS	read-only
			STATUS	current
			::= { hmWanMbusC3 30 }

hmWanMbusC3Value0C		OBJECT-TYPE
			SYNTAX	INTEGER
			MAX-ACCESS	read-only
			STATUS	current
			::= { hmWanMbusC3 31 }

hmWanMbusC3VIF0D		OBJECT-TYPE
			SYNTAX	INTEGER
			MAX-ACCESS	read-only
			STATUS	current
			::= { hmWanMbusC3 32 }

hmWanMbusC3Value0D		OBJECT-TYPE
			SYNTAX	INTEGER
			MAX-ACCESS	read-only
			STATUS	current
			::= { hmWanMbusC3 33 }

hmWanMbusC3VIF0E		OBJECT-TYPE
			SYNTAX	INTEGER
			MAX-ACCESS	read-only
			STATUS	current
			::= { hmWanMbusC3 34 }

hmWanMbusC3Value0E		OBJECT-TYPE
			SYNTAX	INTEGER
			MAX-ACCESS	read-only
			STATUS	current
			::= { hmWanMbusC3 35 }

hmWanMbusC3VIF0F		OBJECT-TYPE
			SYNTAX	INTEGER
			MAX-ACCESS	read-only
			STATUS	current
			::= { hmWanMbusC3 36 }

hmWanMbusC3Value0F		OBJECT-TYPE
			SYNTAX	INTEGER
			MAX-ACCESS	read-only
			STATUS	current
			::= { hmWanMbusC3 37 }

hmWanMbusC3VIF10		OBJECT-TYPE
			SYNTAX	INTEGER
			MAX-ACCESS	read-only
			STATUS	current
			::= { hmWanMbusC3 38 }

hmWanMbusC3Value10		OBJECT-TYPE
			SYNTAX	INTEGER
			MAX-ACCESS	read-only
			STATUS	current
			::= { hmWanMbusC3 39 }

hmWanMbusC3VIF11		OBJECT-TYPE
			SYNTAX	INTEGER
			MAX-ACCESS	read-only
			STATUS	current
			::= { hmWanMbusC3 40 }

hmWanMbusC3Value11		OBJECT-TYPE
			SYNTAX	INTEGER
			MAX-ACCESS	read-only
			STATUS	current
			::= { hmWanMbusC3 41 }

hmWanMbusC3VIF12		OBJECT-TYPE
			SYNTAX	INTEGER
			MAX-ACCESS	read-only
			STATUS	current
			::= { hmWanMbusC3 42 }

hmWanMbusC3Value12		OBJECT-TYPE
			SYNTAX	INTEGER
			MAX-ACCESS	read-only
			STATUS	current
			::= { hmWanMbusC3 43 }

hmWanMbusC3VIF13		OBJECT-TYPE
			SYNTAX	INTEGER
			MAX-ACCESS	read-only
			STATUS	current
			::= { hmWanMbusC3 44 }

hmWanMbusC3Value13		OBJECT-TYPE
			SYNTAX	INTEGER
			MAX-ACCESS	read-only
			STATUS	current
			::= { hmWanMbusC3 45 }

hmWanMbusC3VIF14		OBJECT-TYPE
			SYNTAX	INTEGER
			MAX-ACCESS	read-only
			STATUS	current
			::= { hmWanMbusC3 46 }

hmWanMbusC3Value14		OBJECT-TYPE
			SYNTAX	INTEGER
			MAX-ACCESS	read-only
			STATUS	current
			::= { hmWanMbusC3 47 }

hmWanMbusC3VIF15		OBJECT-TYPE
			SYNTAX	INTEGER
			MAX-ACCESS	read-only
			STATUS	current
			::= { hmWanMbusC3 48 }

hmWanMbusC3Value15		OBJECT-TYPE
			SYNTAX	INTEGER
			MAX-ACCESS	read-only
			STATUS	current
			::= { hmWanMbusC3 49 }

hmWanMbusC3VIF16		OBJECT-TYPE
			SYNTAX	INTEGER
			MAX-ACCESS	read-only
			STATUS	current
			::= { hmWanMbusC3 50 }

hmWanMbusC3Value16		OBJECT-TYPE
			SYNTAX	INTEGER
			MAX-ACCESS	read-only
			STATUS	current
			::= { hmWanMbusC3 51 }

hmWanMbusC3VIF17		OBJECT-TYPE
			SYNTAX	INTEGER
			MAX-ACCESS	read-only
			STATUS	current
			::= { hmWanMbusC3 52 }

hmWanMbusC3Value17		OBJECT-TYPE
			SYNTAX	INTEGER
			MAX-ACCESS	read-only
			STATUS	current
			::= { hmWanMbusC3 53 }

hmWanMbusC3VIF18		OBJECT-TYPE
			SYNTAX	INTEGER
			MAX-ACCESS	read-only
			STATUS	current
			::= { hmWanMbusC3 54 }

hmWanMbusC3Value18		OBJECT-TYPE
			SYNTAX	INTEGER
			MAX-ACCESS	read-only
			STATUS	current
			::= { hmWanMbusC3 55 }

hmWanMbusC3VIF19		OBJECT-TYPE
			SYNTAX	INTEGER
			MAX-ACCESS	read-only
			STATUS	current
			::= { hmWanMbusC3 56 }

hmWanMbusC3Value19		OBJECT-TYPE
			SYNTAX	INTEGER
			MAX-ACCESS	read-only
			STATUS	current
			::= { hmWanMbusC3 57 }

hmWanMbusC3VIF1A		OBJECT-TYPE
			SYNTAX	INTEGER
			MAX-ACCESS	read-only
			STATUS	current
			::= { hmWanMbusC3 58 }

hmWanMbusC3Value1A		OBJECT-TYPE
			SYNTAX	INTEGER
			MAX-ACCESS	read-only
			STATUS	current
			::= { hmWanMbusC3 59 }

hmWanMbusC3VIF1B		OBJECT-TYPE
			SYNTAX	INTEGER
			MAX-ACCESS	read-only
			STATUS	current
			::= { hmWanMbusC3 60 }

hmWanMbusC3Value1B		OBJECT-TYPE
			SYNTAX	INTEGER
			MAX-ACCESS	read-only
			STATUS	current
			::= { hmWanMbusC3 61 }

hmWanMbusC3VIF1C		OBJECT-TYPE
			SYNTAX	INTEGER
			MAX-ACCESS	read-only
			STATUS	current
			::= { hmWanMbusC3 62 }

hmWanMbusC3Value1C		OBJECT-TYPE
			SYNTAX	INTEGER
			MAX-ACCESS	read-only
			STATUS	current
			::= { hmWanMbusC3 63 }

hmWanMbusC3VIF1D		OBJECT-TYPE
			SYNTAX	INTEGER
			MAX-ACCESS	read-only
			STATUS	current
			::= { hmWanMbusC3 64 }

hmWanMbusC3Value1D		OBJECT-TYPE
			SYNTAX	INTEGER
			MAX-ACCESS	read-only
			STATUS	current
			::= { hmWanMbusC3 65 }

hmWanMbusC3VIF1E		OBJECT-TYPE
			SYNTAX	INTEGER
			MAX-ACCESS	read-only
			STATUS	current
			::= { hmWanMbusC3 66 }

hmWanMbusC3Value1E		OBJECT-TYPE
			SYNTAX	INTEGER
			MAX-ACCESS	read-only
			STATUS	current
			::= { hmWanMbusC3 67 }

hmWanMbusC3VIF1F		OBJECT-TYPE
			SYNTAX	INTEGER
			MAX-ACCESS	read-only
			STATUS	current
			::= { hmWanMbusC3 68 }

hmWanMbusC3Value1F		OBJECT-TYPE
			SYNTAX	INTEGER
			MAX-ACCESS	read-only
			STATUS	current
			::= { hmWanMbusC3 69 }

hmWanMbusC3VIF20		OBJECT-TYPE
			SYNTAX	INTEGER
			MAX-ACCESS	read-only
			STATUS	current
			::= { hmWanMbusC3 70 }

hmWanMbusC3Value20		OBJECT-TYPE
			SYNTAX	INTEGER
			MAX-ACCESS	read-only
			STATUS	current
			::= { hmWanMbusC3 71 }

hmWanMbusC3VIF21		OBJECT-TYPE
			SYNTAX	INTEGER
			MAX-ACCESS	read-only
			STATUS	current
			::= { hmWanMbusC3 72 }

hmWanMbusC3Value21		OBJECT-TYPE
			SYNTAX	INTEGER
			MAX-ACCESS	read-only
			STATUS	current
			::= { hmWanMbusC3 73 }

hmWanMbusC3VIF22		OBJECT-TYPE
			SYNTAX	INTEGER
			MAX-ACCESS	read-only
			STATUS	current
			::= { hmWanMbusC3 74 }

hmWanMbusC3Value22		OBJECT-TYPE
			SYNTAX	INTEGER
			MAX-ACCESS	read-only
			STATUS	current
			::= { hmWanMbusC3 75 }

hmWanMbusC3VIF23		OBJECT-TYPE
			SYNTAX	INTEGER
			MAX-ACCESS	read-only
			STATUS	current
			::= { hmWanMbusC3 76 }

hmWanMbusC3Value23		OBJECT-TYPE
			SYNTAX	INTEGER
			MAX-ACCESS	read-only
			STATUS	current
			::= { hmWanMbusC3 77 }

hmWanMbusC3VIF24		OBJECT-TYPE
			SYNTAX	INTEGER
			MAX-ACCESS	read-only
			STATUS	current
			::= { hmWanMbusC3 78 }

hmWanMbusC3Value24		OBJECT-TYPE
			SYNTAX	INTEGER
			MAX-ACCESS	read-only
			STATUS	current
			::= { hmWanMbusC3 79 }

hmWanMbusC3VIF25		OBJECT-TYPE
			SYNTAX	INTEGER
			MAX-ACCESS	read-only
			STATUS	current
			::= { hmWanMbusC3 80 }

hmWanMbusC3Value25		OBJECT-TYPE
			SYNTAX	INTEGER
			MAX-ACCESS	read-only
			STATUS	current
			::= { hmWanMbusC3 81 }

hmWanMbusC3VIF26		OBJECT-TYPE
			SYNTAX	INTEGER
			MAX-ACCESS	read-only
			STATUS	current
			::= { hmWanMbusC3 82 }

hmWanMbusC3Value26		OBJECT-TYPE
			SYNTAX	INTEGER
			MAX-ACCESS	read-only
			STATUS	current
			::= { hmWanMbusC3 83 }

hmWanMbusC3VIF27		OBJECT-TYPE
			SYNTAX	INTEGER
			MAX-ACCESS	read-only
			STATUS	current
			::= { hmWanMbusC3 84 }

hmWanMbusC3Value27		OBJECT-TYPE
			SYNTAX	INTEGER
			MAX-ACCESS	read-only
			STATUS	current
			::= { hmWanMbusC3 85 }

hmWanMbusC3VIF28		OBJECT-TYPE
			SYNTAX	INTEGER
			MAX-ACCESS	read-only
			STATUS	current
			::= { hmWanMbusC3 86 }

hmWanMbusC3Value28		OBJECT-TYPE
			SYNTAX	INTEGER
			MAX-ACCESS	read-only
			STATUS	current
			::= { hmWanMbusC3 87 }

hmWanMbusC3VIF29		OBJECT-TYPE
			SYNTAX	INTEGER
			MAX-ACCESS	read-only
			STATUS	current
			::= { hmWanMbusC3 88 }

hmWanMbusC3Value29		OBJECT-TYPE
			SYNTAX	INTEGER
			MAX-ACCESS	read-only
			STATUS	current
			::= { hmWanMbusC3 89 }

hmWanMbusC3VIF2A		OBJECT-TYPE
			SYNTAX	INTEGER
			MAX-ACCESS	read-only
			STATUS	current
			::= { hmWanMbusC3 90 }

hmWanMbusC3Value2A		OBJECT-TYPE
			SYNTAX	INTEGER
			MAX-ACCESS	read-only
			STATUS	current
			::= { hmWanMbusC3 91 }

hmWanMbusC3VIF2B		OBJECT-TYPE
			SYNTAX	INTEGER
			MAX-ACCESS	read-only
			STATUS	current
			::= { hmWanMbusC3 92 }

hmWanMbusC3Value2B		OBJECT-TYPE
			SYNTAX	INTEGER
			MAX-ACCESS	read-only
			STATUS	current
			::= { hmWanMbusC3 93 }

hmWanMbusC3VIF2C		OBJECT-TYPE
			SYNTAX	INTEGER
			MAX-ACCESS	read-only
			STATUS	current
			::= { hmWanMbusC3 94 }

hmWanMbusC3Value2C		OBJECT-TYPE
			SYNTAX	INTEGER
			MAX-ACCESS	read-only
			STATUS	current
			::= { hmWanMbusC3 95 }

hmWanMbusC3VIF2D		OBJECT-TYPE
			SYNTAX	INTEGER
			MAX-ACCESS	read-only
			STATUS	current
			::= { hmWanMbusC3 96 }

hmWanMbusC3Value2D		OBJECT-TYPE
			SYNTAX	INTEGER
			MAX-ACCESS	read-only
			STATUS	current
			::= { hmWanMbusC3 97 }

hmWanMbusC3VIF2E		OBJECT-TYPE
			SYNTAX	INTEGER
			MAX-ACCESS	read-only
			STATUS	current
			::= { hmWanMbusC3 98 }

hmWanMbusC3Value2E		OBJECT-TYPE
			SYNTAX	INTEGER
			MAX-ACCESS	read-only
			STATUS	current
			::= { hmWanMbusC3 99 }

hmWanMbusC3VIF2F		OBJECT-TYPE
			SYNTAX	INTEGER
			MAX-ACCESS	read-only
			STATUS	current
			::= { hmWanMbusC3 100 }

hmWanMbusC3Value2F		OBJECT-TYPE
			SYNTAX	INTEGER
			MAX-ACCESS	read-only
			STATUS	current
			::= { hmWanMbusC3 101 }

hmWanMbusC4			OBJECT IDENTIFIER ::= { hmWanMbus 196 }

hmWanMbusC4IdNumber		OBJECT-TYPE
			SYNTAX	Gauge32
			MAX-ACCESS	read-only
			STATUS	current
			::= { hmWanMbusC4 1 }

hmWanMbusC4Manufacturer	OBJECT-TYPE
			SYNTAX	Gauge32
			MAX-ACCESS	read-only
			STATUS	current
			::= { hmWanMbusC4 2 }

hmWanMbusC4Version		OBJECT-TYPE
			SYNTAX	Gauge32
			MAX-ACCESS	read-only
			STATUS	current
			::= { hmWanMbusC4 3 }

hmWanMbusC4Medium		OBJECT-TYPE
			SYNTAX	Gauge32
			MAX-ACCESS	read-only
			STATUS	current
			::= { hmWanMbusC4 4 }

hmWanMbusC4Status		OBJECT-TYPE
			SYNTAX	Gauge32
			MAX-ACCESS	read-only
			STATUS	current
			::= { hmWanMbusC4 5 }

hmWanMbusC4VIF00		OBJECT-TYPE
			SYNTAX	INTEGER
			MAX-ACCESS	read-only
			STATUS	current
			::= { hmWanMbusC4 6 }

hmWanMbusC4Value00		OBJECT-TYPE
			SYNTAX	INTEGER
			MAX-ACCESS	read-only
			STATUS	current
			::= { hmWanMbusC4 7 }

hmWanMbusC4VIF01		OBJECT-TYPE
			SYNTAX	INTEGER
			MAX-ACCESS	read-only
			STATUS	current
			::= { hmWanMbusC4 8 }

hmWanMbusC4Value01		OBJECT-TYPE
			SYNTAX	INTEGER
			MAX-ACCESS	read-only
			STATUS	current
			::= { hmWanMbusC4 9 }

hmWanMbusC4VIF02		OBJECT-TYPE
			SYNTAX	INTEGER
			MAX-ACCESS	read-only
			STATUS	current
			::= { hmWanMbusC4 10 }

hmWanMbusC4Value02		OBJECT-TYPE
			SYNTAX	INTEGER
			MAX-ACCESS	read-only
			STATUS	current
			::= { hmWanMbusC4 11 }

hmWanMbusC4VIF03		OBJECT-TYPE
			SYNTAX	INTEGER
			MAX-ACCESS	read-only
			STATUS	current
			::= { hmWanMbusC4 12 }

hmWanMbusC4Value03		OBJECT-TYPE
			SYNTAX	INTEGER
			MAX-ACCESS	read-only
			STATUS	current
			::= { hmWanMbusC4 13 }

hmWanMbusC4VIF04		OBJECT-TYPE
			SYNTAX	INTEGER
			MAX-ACCESS	read-only
			STATUS	current
			::= { hmWanMbusC4 14 }

hmWanMbusC4Value04		OBJECT-TYPE
			SYNTAX	INTEGER
			MAX-ACCESS	read-only
			STATUS	current
			::= { hmWanMbusC4 15 }

hmWanMbusC4VIF05		OBJECT-TYPE
			SYNTAX	INTEGER
			MAX-ACCESS	read-only
			STATUS	current
			::= { hmWanMbusC4 16 }

hmWanMbusC4Value05		OBJECT-TYPE
			SYNTAX	INTEGER
			MAX-ACCESS	read-only
			STATUS	current
			::= { hmWanMbusC4 17 }

hmWanMbusC4VIF06		OBJECT-TYPE
			SYNTAX	INTEGER
			MAX-ACCESS	read-only
			STATUS	current
			::= { hmWanMbusC4 18 }

hmWanMbusC4Value06		OBJECT-TYPE
			SYNTAX	INTEGER
			MAX-ACCESS	read-only
			STATUS	current
			::= { hmWanMbusC4 19 }

hmWanMbusC4VIF07		OBJECT-TYPE
			SYNTAX	INTEGER
			MAX-ACCESS	read-only
			STATUS	current
			::= { hmWanMbusC4 20 }

hmWanMbusC4Value07		OBJECT-TYPE
			SYNTAX	INTEGER
			MAX-ACCESS	read-only
			STATUS	current
			::= { hmWanMbusC4 21 }

hmWanMbusC4VIF08		OBJECT-TYPE
			SYNTAX	INTEGER
			MAX-ACCESS	read-only
			STATUS	current
			::= { hmWanMbusC4 22 }

hmWanMbusC4Value08		OBJECT-TYPE
			SYNTAX	INTEGER
			MAX-ACCESS	read-only
			STATUS	current
			::= { hmWanMbusC4 23 }

hmWanMbusC4VIF09		OBJECT-TYPE
			SYNTAX	INTEGER
			MAX-ACCESS	read-only
			STATUS	current
			::= { hmWanMbusC4 24 }

hmWanMbusC4Value09		OBJECT-TYPE
			SYNTAX	INTEGER
			MAX-ACCESS	read-only
			STATUS	current
			::= { hmWanMbusC4 25 }

hmWanMbusC4VIF0A		OBJECT-TYPE
			SYNTAX	INTEGER
			MAX-ACCESS	read-only
			STATUS	current
			::= { hmWanMbusC4 26 }

hmWanMbusC4Value0A		OBJECT-TYPE
			SYNTAX	INTEGER
			MAX-ACCESS	read-only
			STATUS	current
			::= { hmWanMbusC4 27 }

hmWanMbusC4VIF0B		OBJECT-TYPE
			SYNTAX	INTEGER
			MAX-ACCESS	read-only
			STATUS	current
			::= { hmWanMbusC4 28 }

hmWanMbusC4Value0B		OBJECT-TYPE
			SYNTAX	INTEGER
			MAX-ACCESS	read-only
			STATUS	current
			::= { hmWanMbusC4 29 }

hmWanMbusC4VIF0C		OBJECT-TYPE
			SYNTAX	INTEGER
			MAX-ACCESS	read-only
			STATUS	current
			::= { hmWanMbusC4 30 }

hmWanMbusC4Value0C		OBJECT-TYPE
			SYNTAX	INTEGER
			MAX-ACCESS	read-only
			STATUS	current
			::= { hmWanMbusC4 31 }

hmWanMbusC4VIF0D		OBJECT-TYPE
			SYNTAX	INTEGER
			MAX-ACCESS	read-only
			STATUS	current
			::= { hmWanMbusC4 32 }

hmWanMbusC4Value0D		OBJECT-TYPE
			SYNTAX	INTEGER
			MAX-ACCESS	read-only
			STATUS	current
			::= { hmWanMbusC4 33 }

hmWanMbusC4VIF0E		OBJECT-TYPE
			SYNTAX	INTEGER
			MAX-ACCESS	read-only
			STATUS	current
			::= { hmWanMbusC4 34 }

hmWanMbusC4Value0E		OBJECT-TYPE
			SYNTAX	INTEGER
			MAX-ACCESS	read-only
			STATUS	current
			::= { hmWanMbusC4 35 }

hmWanMbusC4VIF0F		OBJECT-TYPE
			SYNTAX	INTEGER
			MAX-ACCESS	read-only
			STATUS	current
			::= { hmWanMbusC4 36 }

hmWanMbusC4Value0F		OBJECT-TYPE
			SYNTAX	INTEGER
			MAX-ACCESS	read-only
			STATUS	current
			::= { hmWanMbusC4 37 }

hmWanMbusC4VIF10		OBJECT-TYPE
			SYNTAX	INTEGER
			MAX-ACCESS	read-only
			STATUS	current
			::= { hmWanMbusC4 38 }

hmWanMbusC4Value10		OBJECT-TYPE
			SYNTAX	INTEGER
			MAX-ACCESS	read-only
			STATUS	current
			::= { hmWanMbusC4 39 }

hmWanMbusC4VIF11		OBJECT-TYPE
			SYNTAX	INTEGER
			MAX-ACCESS	read-only
			STATUS	current
			::= { hmWanMbusC4 40 }

hmWanMbusC4Value11		OBJECT-TYPE
			SYNTAX	INTEGER
			MAX-ACCESS	read-only
			STATUS	current
			::= { hmWanMbusC4 41 }

hmWanMbusC4VIF12		OBJECT-TYPE
			SYNTAX	INTEGER
			MAX-ACCESS	read-only
			STATUS	current
			::= { hmWanMbusC4 42 }

hmWanMbusC4Value12		OBJECT-TYPE
			SYNTAX	INTEGER
			MAX-ACCESS	read-only
			STATUS	current
			::= { hmWanMbusC4 43 }

hmWanMbusC4VIF13		OBJECT-TYPE
			SYNTAX	INTEGER
			MAX-ACCESS	read-only
			STATUS	current
			::= { hmWanMbusC4 44 }

hmWanMbusC4Value13		OBJECT-TYPE
			SYNTAX	INTEGER
			MAX-ACCESS	read-only
			STATUS	current
			::= { hmWanMbusC4 45 }

hmWanMbusC4VIF14		OBJECT-TYPE
			SYNTAX	INTEGER
			MAX-ACCESS	read-only
			STATUS	current
			::= { hmWanMbusC4 46 }

hmWanMbusC4Value14		OBJECT-TYPE
			SYNTAX	INTEGER
			MAX-ACCESS	read-only
			STATUS	current
			::= { hmWanMbusC4 47 }

hmWanMbusC4VIF15		OBJECT-TYPE
			SYNTAX	INTEGER
			MAX-ACCESS	read-only
			STATUS	current
			::= { hmWanMbusC4 48 }

hmWanMbusC4Value15		OBJECT-TYPE
			SYNTAX	INTEGER
			MAX-ACCESS	read-only
			STATUS	current
			::= { hmWanMbusC4 49 }

hmWanMbusC4VIF16		OBJECT-TYPE
			SYNTAX	INTEGER
			MAX-ACCESS	read-only
			STATUS	current
			::= { hmWanMbusC4 50 }

hmWanMbusC4Value16		OBJECT-TYPE
			SYNTAX	INTEGER
			MAX-ACCESS	read-only
			STATUS	current
			::= { hmWanMbusC4 51 }

hmWanMbusC4VIF17		OBJECT-TYPE
			SYNTAX	INTEGER
			MAX-ACCESS	read-only
			STATUS	current
			::= { hmWanMbusC4 52 }

hmWanMbusC4Value17		OBJECT-TYPE
			SYNTAX	INTEGER
			MAX-ACCESS	read-only
			STATUS	current
			::= { hmWanMbusC4 53 }

hmWanMbusC4VIF18		OBJECT-TYPE
			SYNTAX	INTEGER
			MAX-ACCESS	read-only
			STATUS	current
			::= { hmWanMbusC4 54 }

hmWanMbusC4Value18		OBJECT-TYPE
			SYNTAX	INTEGER
			MAX-ACCESS	read-only
			STATUS	current
			::= { hmWanMbusC4 55 }

hmWanMbusC4VIF19		OBJECT-TYPE
			SYNTAX	INTEGER
			MAX-ACCESS	read-only
			STATUS	current
			::= { hmWanMbusC4 56 }

hmWanMbusC4Value19		OBJECT-TYPE
			SYNTAX	INTEGER
			MAX-ACCESS	read-only
			STATUS	current
			::= { hmWanMbusC4 57 }

hmWanMbusC4VIF1A		OBJECT-TYPE
			SYNTAX	INTEGER
			MAX-ACCESS	read-only
			STATUS	current
			::= { hmWanMbusC4 58 }

hmWanMbusC4Value1A		OBJECT-TYPE
			SYNTAX	INTEGER
			MAX-ACCESS	read-only
			STATUS	current
			::= { hmWanMbusC4 59 }

hmWanMbusC4VIF1B		OBJECT-TYPE
			SYNTAX	INTEGER
			MAX-ACCESS	read-only
			STATUS	current
			::= { hmWanMbusC4 60 }

hmWanMbusC4Value1B		OBJECT-TYPE
			SYNTAX	INTEGER
			MAX-ACCESS	read-only
			STATUS	current
			::= { hmWanMbusC4 61 }

hmWanMbusC4VIF1C		OBJECT-TYPE
			SYNTAX	INTEGER
			MAX-ACCESS	read-only
			STATUS	current
			::= { hmWanMbusC4 62 }

hmWanMbusC4Value1C		OBJECT-TYPE
			SYNTAX	INTEGER
			MAX-ACCESS	read-only
			STATUS	current
			::= { hmWanMbusC4 63 }

hmWanMbusC4VIF1D		OBJECT-TYPE
			SYNTAX	INTEGER
			MAX-ACCESS	read-only
			STATUS	current
			::= { hmWanMbusC4 64 }

hmWanMbusC4Value1D		OBJECT-TYPE
			SYNTAX	INTEGER
			MAX-ACCESS	read-only
			STATUS	current
			::= { hmWanMbusC4 65 }

hmWanMbusC4VIF1E		OBJECT-TYPE
			SYNTAX	INTEGER
			MAX-ACCESS	read-only
			STATUS	current
			::= { hmWanMbusC4 66 }

hmWanMbusC4Value1E		OBJECT-TYPE
			SYNTAX	INTEGER
			MAX-ACCESS	read-only
			STATUS	current
			::= { hmWanMbusC4 67 }

hmWanMbusC4VIF1F		OBJECT-TYPE
			SYNTAX	INTEGER
			MAX-ACCESS	read-only
			STATUS	current
			::= { hmWanMbusC4 68 }

hmWanMbusC4Value1F		OBJECT-TYPE
			SYNTAX	INTEGER
			MAX-ACCESS	read-only
			STATUS	current
			::= { hmWanMbusC4 69 }

hmWanMbusC4VIF20		OBJECT-TYPE
			SYNTAX	INTEGER
			MAX-ACCESS	read-only
			STATUS	current
			::= { hmWanMbusC4 70 }

hmWanMbusC4Value20		OBJECT-TYPE
			SYNTAX	INTEGER
			MAX-ACCESS	read-only
			STATUS	current
			::= { hmWanMbusC4 71 }

hmWanMbusC4VIF21		OBJECT-TYPE
			SYNTAX	INTEGER
			MAX-ACCESS	read-only
			STATUS	current
			::= { hmWanMbusC4 72 }

hmWanMbusC4Value21		OBJECT-TYPE
			SYNTAX	INTEGER
			MAX-ACCESS	read-only
			STATUS	current
			::= { hmWanMbusC4 73 }

hmWanMbusC4VIF22		OBJECT-TYPE
			SYNTAX	INTEGER
			MAX-ACCESS	read-only
			STATUS	current
			::= { hmWanMbusC4 74 }

hmWanMbusC4Value22		OBJECT-TYPE
			SYNTAX	INTEGER
			MAX-ACCESS	read-only
			STATUS	current
			::= { hmWanMbusC4 75 }

hmWanMbusC4VIF23		OBJECT-TYPE
			SYNTAX	INTEGER
			MAX-ACCESS	read-only
			STATUS	current
			::= { hmWanMbusC4 76 }

hmWanMbusC4Value23		OBJECT-TYPE
			SYNTAX	INTEGER
			MAX-ACCESS	read-only
			STATUS	current
			::= { hmWanMbusC4 77 }

hmWanMbusC4VIF24		OBJECT-TYPE
			SYNTAX	INTEGER
			MAX-ACCESS	read-only
			STATUS	current
			::= { hmWanMbusC4 78 }

hmWanMbusC4Value24		OBJECT-TYPE
			SYNTAX	INTEGER
			MAX-ACCESS	read-only
			STATUS	current
			::= { hmWanMbusC4 79 }

hmWanMbusC4VIF25		OBJECT-TYPE
			SYNTAX	INTEGER
			MAX-ACCESS	read-only
			STATUS	current
			::= { hmWanMbusC4 80 }

hmWanMbusC4Value25		OBJECT-TYPE
			SYNTAX	INTEGER
			MAX-ACCESS	read-only
			STATUS	current
			::= { hmWanMbusC4 81 }

hmWanMbusC4VIF26		OBJECT-TYPE
			SYNTAX	INTEGER
			MAX-ACCESS	read-only
			STATUS	current
			::= { hmWanMbusC4 82 }

hmWanMbusC4Value26		OBJECT-TYPE
			SYNTAX	INTEGER
			MAX-ACCESS	read-only
			STATUS	current
			::= { hmWanMbusC4 83 }

hmWanMbusC4VIF27		OBJECT-TYPE
			SYNTAX	INTEGER
			MAX-ACCESS	read-only
			STATUS	current
			::= { hmWanMbusC4 84 }

hmWanMbusC4Value27		OBJECT-TYPE
			SYNTAX	INTEGER
			MAX-ACCESS	read-only
			STATUS	current
			::= { hmWanMbusC4 85 }

hmWanMbusC4VIF28		OBJECT-TYPE
			SYNTAX	INTEGER
			MAX-ACCESS	read-only
			STATUS	current
			::= { hmWanMbusC4 86 }

hmWanMbusC4Value28		OBJECT-TYPE
			SYNTAX	INTEGER
			MAX-ACCESS	read-only
			STATUS	current
			::= { hmWanMbusC4 87 }

hmWanMbusC4VIF29		OBJECT-TYPE
			SYNTAX	INTEGER
			MAX-ACCESS	read-only
			STATUS	current
			::= { hmWanMbusC4 88 }

hmWanMbusC4Value29		OBJECT-TYPE
			SYNTAX	INTEGER
			MAX-ACCESS	read-only
			STATUS	current
			::= { hmWanMbusC4 89 }

hmWanMbusC4VIF2A		OBJECT-TYPE
			SYNTAX	INTEGER
			MAX-ACCESS	read-only
			STATUS	current
			::= { hmWanMbusC4 90 }

hmWanMbusC4Value2A		OBJECT-TYPE
			SYNTAX	INTEGER
			MAX-ACCESS	read-only
			STATUS	current
			::= { hmWanMbusC4 91 }

hmWanMbusC4VIF2B		OBJECT-TYPE
			SYNTAX	INTEGER
			MAX-ACCESS	read-only
			STATUS	current
			::= { hmWanMbusC4 92 }

hmWanMbusC4Value2B		OBJECT-TYPE
			SYNTAX	INTEGER
			MAX-ACCESS	read-only
			STATUS	current
			::= { hmWanMbusC4 93 }

hmWanMbusC4VIF2C		OBJECT-TYPE
			SYNTAX	INTEGER
			MAX-ACCESS	read-only
			STATUS	current
			::= { hmWanMbusC4 94 }

hmWanMbusC4Value2C		OBJECT-TYPE
			SYNTAX	INTEGER
			MAX-ACCESS	read-only
			STATUS	current
			::= { hmWanMbusC4 95 }

hmWanMbusC4VIF2D		OBJECT-TYPE
			SYNTAX	INTEGER
			MAX-ACCESS	read-only
			STATUS	current
			::= { hmWanMbusC4 96 }

hmWanMbusC4Value2D		OBJECT-TYPE
			SYNTAX	INTEGER
			MAX-ACCESS	read-only
			STATUS	current
			::= { hmWanMbusC4 97 }

hmWanMbusC4VIF2E		OBJECT-TYPE
			SYNTAX	INTEGER
			MAX-ACCESS	read-only
			STATUS	current
			::= { hmWanMbusC4 98 }

hmWanMbusC4Value2E		OBJECT-TYPE
			SYNTAX	INTEGER
			MAX-ACCESS	read-only
			STATUS	current
			::= { hmWanMbusC4 99 }

hmWanMbusC4VIF2F		OBJECT-TYPE
			SYNTAX	INTEGER
			MAX-ACCESS	read-only
			STATUS	current
			::= { hmWanMbusC4 100 }

hmWanMbusC4Value2F		OBJECT-TYPE
			SYNTAX	INTEGER
			MAX-ACCESS	read-only
			STATUS	current
			::= { hmWanMbusC4 101 }

hmWanMbusC5			OBJECT IDENTIFIER ::= { hmWanMbus 197 }

hmWanMbusC5IdNumber		OBJECT-TYPE
			SYNTAX	Gauge32
			MAX-ACCESS	read-only
			STATUS	current
			::= { hmWanMbusC5 1 }

hmWanMbusC5Manufacturer	OBJECT-TYPE
			SYNTAX	Gauge32
			MAX-ACCESS	read-only
			STATUS	current
			::= { hmWanMbusC5 2 }

hmWanMbusC5Version		OBJECT-TYPE
			SYNTAX	Gauge32
			MAX-ACCESS	read-only
			STATUS	current
			::= { hmWanMbusC5 3 }

hmWanMbusC5Medium		OBJECT-TYPE
			SYNTAX	Gauge32
			MAX-ACCESS	read-only
			STATUS	current
			::= { hmWanMbusC5 4 }

hmWanMbusC5Status		OBJECT-TYPE
			SYNTAX	Gauge32
			MAX-ACCESS	read-only
			STATUS	current
			::= { hmWanMbusC5 5 }

hmWanMbusC5VIF00		OBJECT-TYPE
			SYNTAX	INTEGER
			MAX-ACCESS	read-only
			STATUS	current
			::= { hmWanMbusC5 6 }

hmWanMbusC5Value00		OBJECT-TYPE
			SYNTAX	INTEGER
			MAX-ACCESS	read-only
			STATUS	current
			::= { hmWanMbusC5 7 }

hmWanMbusC5VIF01		OBJECT-TYPE
			SYNTAX	INTEGER
			MAX-ACCESS	read-only
			STATUS	current
			::= { hmWanMbusC5 8 }

hmWanMbusC5Value01		OBJECT-TYPE
			SYNTAX	INTEGER
			MAX-ACCESS	read-only
			STATUS	current
			::= { hmWanMbusC5 9 }

hmWanMbusC5VIF02		OBJECT-TYPE
			SYNTAX	INTEGER
			MAX-ACCESS	read-only
			STATUS	current
			::= { hmWanMbusC5 10 }

hmWanMbusC5Value02		OBJECT-TYPE
			SYNTAX	INTEGER
			MAX-ACCESS	read-only
			STATUS	current
			::= { hmWanMbusC5 11 }

hmWanMbusC5VIF03		OBJECT-TYPE
			SYNTAX	INTEGER
			MAX-ACCESS	read-only
			STATUS	current
			::= { hmWanMbusC5 12 }

hmWanMbusC5Value03		OBJECT-TYPE
			SYNTAX	INTEGER
			MAX-ACCESS	read-only
			STATUS	current
			::= { hmWanMbusC5 13 }

hmWanMbusC5VIF04		OBJECT-TYPE
			SYNTAX	INTEGER
			MAX-ACCESS	read-only
			STATUS	current
			::= { hmWanMbusC5 14 }

hmWanMbusC5Value04		OBJECT-TYPE
			SYNTAX	INTEGER
			MAX-ACCESS	read-only
			STATUS	current
			::= { hmWanMbusC5 15 }

hmWanMbusC5VIF05		OBJECT-TYPE
			SYNTAX	INTEGER
			MAX-ACCESS	read-only
			STATUS	current
			::= { hmWanMbusC5 16 }

hmWanMbusC5Value05		OBJECT-TYPE
			SYNTAX	INTEGER
			MAX-ACCESS	read-only
			STATUS	current
			::= { hmWanMbusC5 17 }

hmWanMbusC5VIF06		OBJECT-TYPE
			SYNTAX	INTEGER
			MAX-ACCESS	read-only
			STATUS	current
			::= { hmWanMbusC5 18 }

hmWanMbusC5Value06		OBJECT-TYPE
			SYNTAX	INTEGER
			MAX-ACCESS	read-only
			STATUS	current
			::= { hmWanMbusC5 19 }

hmWanMbusC5VIF07		OBJECT-TYPE
			SYNTAX	INTEGER
			MAX-ACCESS	read-only
			STATUS	current
			::= { hmWanMbusC5 20 }

hmWanMbusC5Value07		OBJECT-TYPE
			SYNTAX	INTEGER
			MAX-ACCESS	read-only
			STATUS	current
			::= { hmWanMbusC5 21 }

hmWanMbusC5VIF08		OBJECT-TYPE
			SYNTAX	INTEGER
			MAX-ACCESS	read-only
			STATUS	current
			::= { hmWanMbusC5 22 }

hmWanMbusC5Value08		OBJECT-TYPE
			SYNTAX	INTEGER
			MAX-ACCESS	read-only
			STATUS	current
			::= { hmWanMbusC5 23 }

hmWanMbusC5VIF09		OBJECT-TYPE
			SYNTAX	INTEGER
			MAX-ACCESS	read-only
			STATUS	current
			::= { hmWanMbusC5 24 }

hmWanMbusC5Value09		OBJECT-TYPE
			SYNTAX	INTEGER
			MAX-ACCESS	read-only
			STATUS	current
			::= { hmWanMbusC5 25 }

hmWanMbusC5VIF0A		OBJECT-TYPE
			SYNTAX	INTEGER
			MAX-ACCESS	read-only
			STATUS	current
			::= { hmWanMbusC5 26 }

hmWanMbusC5Value0A		OBJECT-TYPE
			SYNTAX	INTEGER
			MAX-ACCESS	read-only
			STATUS	current
			::= { hmWanMbusC5 27 }

hmWanMbusC5VIF0B		OBJECT-TYPE
			SYNTAX	INTEGER
			MAX-ACCESS	read-only
			STATUS	current
			::= { hmWanMbusC5 28 }

hmWanMbusC5Value0B		OBJECT-TYPE
			SYNTAX	INTEGER
			MAX-ACCESS	read-only
			STATUS	current
			::= { hmWanMbusC5 29 }

hmWanMbusC5VIF0C		OBJECT-TYPE
			SYNTAX	INTEGER
			MAX-ACCESS	read-only
			STATUS	current
			::= { hmWanMbusC5 30 }

hmWanMbusC5Value0C		OBJECT-TYPE
			SYNTAX	INTEGER
			MAX-ACCESS	read-only
			STATUS	current
			::= { hmWanMbusC5 31 }

hmWanMbusC5VIF0D		OBJECT-TYPE
			SYNTAX	INTEGER
			MAX-ACCESS	read-only
			STATUS	current
			::= { hmWanMbusC5 32 }

hmWanMbusC5Value0D		OBJECT-TYPE
			SYNTAX	INTEGER
			MAX-ACCESS	read-only
			STATUS	current
			::= { hmWanMbusC5 33 }

hmWanMbusC5VIF0E		OBJECT-TYPE
			SYNTAX	INTEGER
			MAX-ACCESS	read-only
			STATUS	current
			::= { hmWanMbusC5 34 }

hmWanMbusC5Value0E		OBJECT-TYPE
			SYNTAX	INTEGER
			MAX-ACCESS	read-only
			STATUS	current
			::= { hmWanMbusC5 35 }

hmWanMbusC5VIF0F		OBJECT-TYPE
			SYNTAX	INTEGER
			MAX-ACCESS	read-only
			STATUS	current
			::= { hmWanMbusC5 36 }

hmWanMbusC5Value0F		OBJECT-TYPE
			SYNTAX	INTEGER
			MAX-ACCESS	read-only
			STATUS	current
			::= { hmWanMbusC5 37 }

hmWanMbusC5VIF10		OBJECT-TYPE
			SYNTAX	INTEGER
			MAX-ACCESS	read-only
			STATUS	current
			::= { hmWanMbusC5 38 }

hmWanMbusC5Value10		OBJECT-TYPE
			SYNTAX	INTEGER
			MAX-ACCESS	read-only
			STATUS	current
			::= { hmWanMbusC5 39 }

hmWanMbusC5VIF11		OBJECT-TYPE
			SYNTAX	INTEGER
			MAX-ACCESS	read-only
			STATUS	current
			::= { hmWanMbusC5 40 }

hmWanMbusC5Value11		OBJECT-TYPE
			SYNTAX	INTEGER
			MAX-ACCESS	read-only
			STATUS	current
			::= { hmWanMbusC5 41 }

hmWanMbusC5VIF12		OBJECT-TYPE
			SYNTAX	INTEGER
			MAX-ACCESS	read-only
			STATUS	current
			::= { hmWanMbusC5 42 }

hmWanMbusC5Value12		OBJECT-TYPE
			SYNTAX	INTEGER
			MAX-ACCESS	read-only
			STATUS	current
			::= { hmWanMbusC5 43 }

hmWanMbusC5VIF13		OBJECT-TYPE
			SYNTAX	INTEGER
			MAX-ACCESS	read-only
			STATUS	current
			::= { hmWanMbusC5 44 }

hmWanMbusC5Value13		OBJECT-TYPE
			SYNTAX	INTEGER
			MAX-ACCESS	read-only
			STATUS	current
			::= { hmWanMbusC5 45 }

hmWanMbusC5VIF14		OBJECT-TYPE
			SYNTAX	INTEGER
			MAX-ACCESS	read-only
			STATUS	current
			::= { hmWanMbusC5 46 }

hmWanMbusC5Value14		OBJECT-TYPE
			SYNTAX	INTEGER
			MAX-ACCESS	read-only
			STATUS	current
			::= { hmWanMbusC5 47 }

hmWanMbusC5VIF15		OBJECT-TYPE
			SYNTAX	INTEGER
			MAX-ACCESS	read-only
			STATUS	current
			::= { hmWanMbusC5 48 }

hmWanMbusC5Value15		OBJECT-TYPE
			SYNTAX	INTEGER
			MAX-ACCESS	read-only
			STATUS	current
			::= { hmWanMbusC5 49 }

hmWanMbusC5VIF16		OBJECT-TYPE
			SYNTAX	INTEGER
			MAX-ACCESS	read-only
			STATUS	current
			::= { hmWanMbusC5 50 }

hmWanMbusC5Value16		OBJECT-TYPE
			SYNTAX	INTEGER
			MAX-ACCESS	read-only
			STATUS	current
			::= { hmWanMbusC5 51 }

hmWanMbusC5VIF17		OBJECT-TYPE
			SYNTAX	INTEGER
			MAX-ACCESS	read-only
			STATUS	current
			::= { hmWanMbusC5 52 }

hmWanMbusC5Value17		OBJECT-TYPE
			SYNTAX	INTEGER
			MAX-ACCESS	read-only
			STATUS	current
			::= { hmWanMbusC5 53 }

hmWanMbusC5VIF18		OBJECT-TYPE
			SYNTAX	INTEGER
			MAX-ACCESS	read-only
			STATUS	current
			::= { hmWanMbusC5 54 }

hmWanMbusC5Value18		OBJECT-TYPE
			SYNTAX	INTEGER
			MAX-ACCESS	read-only
			STATUS	current
			::= { hmWanMbusC5 55 }

hmWanMbusC5VIF19		OBJECT-TYPE
			SYNTAX	INTEGER
			MAX-ACCESS	read-only
			STATUS	current
			::= { hmWanMbusC5 56 }

hmWanMbusC5Value19		OBJECT-TYPE
			SYNTAX	INTEGER
			MAX-ACCESS	read-only
			STATUS	current
			::= { hmWanMbusC5 57 }

hmWanMbusC5VIF1A		OBJECT-TYPE
			SYNTAX	INTEGER
			MAX-ACCESS	read-only
			STATUS	current
			::= { hmWanMbusC5 58 }

hmWanMbusC5Value1A		OBJECT-TYPE
			SYNTAX	INTEGER
			MAX-ACCESS	read-only
			STATUS	current
			::= { hmWanMbusC5 59 }

hmWanMbusC5VIF1B		OBJECT-TYPE
			SYNTAX	INTEGER
			MAX-ACCESS	read-only
			STATUS	current
			::= { hmWanMbusC5 60 }

hmWanMbusC5Value1B		OBJECT-TYPE
			SYNTAX	INTEGER
			MAX-ACCESS	read-only
			STATUS	current
			::= { hmWanMbusC5 61 }

hmWanMbusC5VIF1C		OBJECT-TYPE
			SYNTAX	INTEGER
			MAX-ACCESS	read-only
			STATUS	current
			::= { hmWanMbusC5 62 }

hmWanMbusC5Value1C		OBJECT-TYPE
			SYNTAX	INTEGER
			MAX-ACCESS	read-only
			STATUS	current
			::= { hmWanMbusC5 63 }

hmWanMbusC5VIF1D		OBJECT-TYPE
			SYNTAX	INTEGER
			MAX-ACCESS	read-only
			STATUS	current
			::= { hmWanMbusC5 64 }

hmWanMbusC5Value1D		OBJECT-TYPE
			SYNTAX	INTEGER
			MAX-ACCESS	read-only
			STATUS	current
			::= { hmWanMbusC5 65 }

hmWanMbusC5VIF1E		OBJECT-TYPE
			SYNTAX	INTEGER
			MAX-ACCESS	read-only
			STATUS	current
			::= { hmWanMbusC5 66 }

hmWanMbusC5Value1E		OBJECT-TYPE
			SYNTAX	INTEGER
			MAX-ACCESS	read-only
			STATUS	current
			::= { hmWanMbusC5 67 }

hmWanMbusC5VIF1F		OBJECT-TYPE
			SYNTAX	INTEGER
			MAX-ACCESS	read-only
			STATUS	current
			::= { hmWanMbusC5 68 }

hmWanMbusC5Value1F		OBJECT-TYPE
			SYNTAX	INTEGER
			MAX-ACCESS	read-only
			STATUS	current
			::= { hmWanMbusC5 69 }

hmWanMbusC5VIF20		OBJECT-TYPE
			SYNTAX	INTEGER
			MAX-ACCESS	read-only
			STATUS	current
			::= { hmWanMbusC5 70 }

hmWanMbusC5Value20		OBJECT-TYPE
			SYNTAX	INTEGER
			MAX-ACCESS	read-only
			STATUS	current
			::= { hmWanMbusC5 71 }

hmWanMbusC5VIF21		OBJECT-TYPE
			SYNTAX	INTEGER
			MAX-ACCESS	read-only
			STATUS	current
			::= { hmWanMbusC5 72 }

hmWanMbusC5Value21		OBJECT-TYPE
			SYNTAX	INTEGER
			MAX-ACCESS	read-only
			STATUS	current
			::= { hmWanMbusC5 73 }

hmWanMbusC5VIF22		OBJECT-TYPE
			SYNTAX	INTEGER
			MAX-ACCESS	read-only
			STATUS	current
			::= { hmWanMbusC5 74 }

hmWanMbusC5Value22		OBJECT-TYPE
			SYNTAX	INTEGER
			MAX-ACCESS	read-only
			STATUS	current
			::= { hmWanMbusC5 75 }

hmWanMbusC5VIF23		OBJECT-TYPE
			SYNTAX	INTEGER
			MAX-ACCESS	read-only
			STATUS	current
			::= { hmWanMbusC5 76 }

hmWanMbusC5Value23		OBJECT-TYPE
			SYNTAX	INTEGER
			MAX-ACCESS	read-only
			STATUS	current
			::= { hmWanMbusC5 77 }

hmWanMbusC5VIF24		OBJECT-TYPE
			SYNTAX	INTEGER
			MAX-ACCESS	read-only
			STATUS	current
			::= { hmWanMbusC5 78 }

hmWanMbusC5Value24		OBJECT-TYPE
			SYNTAX	INTEGER
			MAX-ACCESS	read-only
			STATUS	current
			::= { hmWanMbusC5 79 }

hmWanMbusC5VIF25		OBJECT-TYPE
			SYNTAX	INTEGER
			MAX-ACCESS	read-only
			STATUS	current
			::= { hmWanMbusC5 80 }

hmWanMbusC5Value25		OBJECT-TYPE
			SYNTAX	INTEGER
			MAX-ACCESS	read-only
			STATUS	current
			::= { hmWanMbusC5 81 }

hmWanMbusC5VIF26		OBJECT-TYPE
			SYNTAX	INTEGER
			MAX-ACCESS	read-only
			STATUS	current
			::= { hmWanMbusC5 82 }

hmWanMbusC5Value26		OBJECT-TYPE
			SYNTAX	INTEGER
			MAX-ACCESS	read-only
			STATUS	current
			::= { hmWanMbusC5 83 }

hmWanMbusC5VIF27		OBJECT-TYPE
			SYNTAX	INTEGER
			MAX-ACCESS	read-only
			STATUS	current
			::= { hmWanMbusC5 84 }

hmWanMbusC5Value27		OBJECT-TYPE
			SYNTAX	INTEGER
			MAX-ACCESS	read-only
			STATUS	current
			::= { hmWanMbusC5 85 }

hmWanMbusC5VIF28		OBJECT-TYPE
			SYNTAX	INTEGER
			MAX-ACCESS	read-only
			STATUS	current
			::= { hmWanMbusC5 86 }

hmWanMbusC5Value28		OBJECT-TYPE
			SYNTAX	INTEGER
			MAX-ACCESS	read-only
			STATUS	current
			::= { hmWanMbusC5 87 }

hmWanMbusC5VIF29		OBJECT-TYPE
			SYNTAX	INTEGER
			MAX-ACCESS	read-only
			STATUS	current
			::= { hmWanMbusC5 88 }

hmWanMbusC5Value29		OBJECT-TYPE
			SYNTAX	INTEGER
			MAX-ACCESS	read-only
			STATUS	current
			::= { hmWanMbusC5 89 }

hmWanMbusC5VIF2A		OBJECT-TYPE
			SYNTAX	INTEGER
			MAX-ACCESS	read-only
			STATUS	current
			::= { hmWanMbusC5 90 }

hmWanMbusC5Value2A		OBJECT-TYPE
			SYNTAX	INTEGER
			MAX-ACCESS	read-only
			STATUS	current
			::= { hmWanMbusC5 91 }

hmWanMbusC5VIF2B		OBJECT-TYPE
			SYNTAX	INTEGER
			MAX-ACCESS	read-only
			STATUS	current
			::= { hmWanMbusC5 92 }

hmWanMbusC5Value2B		OBJECT-TYPE
			SYNTAX	INTEGER
			MAX-ACCESS	read-only
			STATUS	current
			::= { hmWanMbusC5 93 }

hmWanMbusC5VIF2C		OBJECT-TYPE
			SYNTAX	INTEGER
			MAX-ACCESS	read-only
			STATUS	current
			::= { hmWanMbusC5 94 }

hmWanMbusC5Value2C		OBJECT-TYPE
			SYNTAX	INTEGER
			MAX-ACCESS	read-only
			STATUS	current
			::= { hmWanMbusC5 95 }

hmWanMbusC5VIF2D		OBJECT-TYPE
			SYNTAX	INTEGER
			MAX-ACCESS	read-only
			STATUS	current
			::= { hmWanMbusC5 96 }

hmWanMbusC5Value2D		OBJECT-TYPE
			SYNTAX	INTEGER
			MAX-ACCESS	read-only
			STATUS	current
			::= { hmWanMbusC5 97 }

hmWanMbusC5VIF2E		OBJECT-TYPE
			SYNTAX	INTEGER
			MAX-ACCESS	read-only
			STATUS	current
			::= { hmWanMbusC5 98 }

hmWanMbusC5Value2E		OBJECT-TYPE
			SYNTAX	INTEGER
			MAX-ACCESS	read-only
			STATUS	current
			::= { hmWanMbusC5 99 }

hmWanMbusC5VIF2F		OBJECT-TYPE
			SYNTAX	INTEGER
			MAX-ACCESS	read-only
			STATUS	current
			::= { hmWanMbusC5 100 }

hmWanMbusC5Value2F		OBJECT-TYPE
			SYNTAX	INTEGER
			MAX-ACCESS	read-only
			STATUS	current
			::= { hmWanMbusC5 101 }

hmWanMbusC6			OBJECT IDENTIFIER ::= { hmWanMbus 198 }

hmWanMbusC6IdNumber		OBJECT-TYPE
			SYNTAX	Gauge32
			MAX-ACCESS	read-only
			STATUS	current
			::= { hmWanMbusC6 1 }

hmWanMbusC6Manufacturer	OBJECT-TYPE
			SYNTAX	Gauge32
			MAX-ACCESS	read-only
			STATUS	current
			::= { hmWanMbusC6 2 }

hmWanMbusC6Version		OBJECT-TYPE
			SYNTAX	Gauge32
			MAX-ACCESS	read-only
			STATUS	current
			::= { hmWanMbusC6 3 }

hmWanMbusC6Medium		OBJECT-TYPE
			SYNTAX	Gauge32
			MAX-ACCESS	read-only
			STATUS	current
			::= { hmWanMbusC6 4 }

hmWanMbusC6Status		OBJECT-TYPE
			SYNTAX	Gauge32
			MAX-ACCESS	read-only
			STATUS	current
			::= { hmWanMbusC6 5 }

hmWanMbusC6VIF00		OBJECT-TYPE
			SYNTAX	INTEGER
			MAX-ACCESS	read-only
			STATUS	current
			::= { hmWanMbusC6 6 }

hmWanMbusC6Value00		OBJECT-TYPE
			SYNTAX	INTEGER
			MAX-ACCESS	read-only
			STATUS	current
			::= { hmWanMbusC6 7 }

hmWanMbusC6VIF01		OBJECT-TYPE
			SYNTAX	INTEGER
			MAX-ACCESS	read-only
			STATUS	current
			::= { hmWanMbusC6 8 }

hmWanMbusC6Value01		OBJECT-TYPE
			SYNTAX	INTEGER
			MAX-ACCESS	read-only
			STATUS	current
			::= { hmWanMbusC6 9 }

hmWanMbusC6VIF02		OBJECT-TYPE
			SYNTAX	INTEGER
			MAX-ACCESS	read-only
			STATUS	current
			::= { hmWanMbusC6 10 }

hmWanMbusC6Value02		OBJECT-TYPE
			SYNTAX	INTEGER
			MAX-ACCESS	read-only
			STATUS	current
			::= { hmWanMbusC6 11 }

hmWanMbusC6VIF03		OBJECT-TYPE
			SYNTAX	INTEGER
			MAX-ACCESS	read-only
			STATUS	current
			::= { hmWanMbusC6 12 }

hmWanMbusC6Value03		OBJECT-TYPE
			SYNTAX	INTEGER
			MAX-ACCESS	read-only
			STATUS	current
			::= { hmWanMbusC6 13 }

hmWanMbusC6VIF04		OBJECT-TYPE
			SYNTAX	INTEGER
			MAX-ACCESS	read-only
			STATUS	current
			::= { hmWanMbusC6 14 }

hmWanMbusC6Value04		OBJECT-TYPE
			SYNTAX	INTEGER
			MAX-ACCESS	read-only
			STATUS	current
			::= { hmWanMbusC6 15 }

hmWanMbusC6VIF05		OBJECT-TYPE
			SYNTAX	INTEGER
			MAX-ACCESS	read-only
			STATUS	current
			::= { hmWanMbusC6 16 }

hmWanMbusC6Value05		OBJECT-TYPE
			SYNTAX	INTEGER
			MAX-ACCESS	read-only
			STATUS	current
			::= { hmWanMbusC6 17 }

hmWanMbusC6VIF06		OBJECT-TYPE
			SYNTAX	INTEGER
			MAX-ACCESS	read-only
			STATUS	current
			::= { hmWanMbusC6 18 }

hmWanMbusC6Value06		OBJECT-TYPE
			SYNTAX	INTEGER
			MAX-ACCESS	read-only
			STATUS	current
			::= { hmWanMbusC6 19 }

hmWanMbusC6VIF07		OBJECT-TYPE
			SYNTAX	INTEGER
			MAX-ACCESS	read-only
			STATUS	current
			::= { hmWanMbusC6 20 }

hmWanMbusC6Value07		OBJECT-TYPE
			SYNTAX	INTEGER
			MAX-ACCESS	read-only
			STATUS	current
			::= { hmWanMbusC6 21 }

hmWanMbusC6VIF08		OBJECT-TYPE
			SYNTAX	INTEGER
			MAX-ACCESS	read-only
			STATUS	current
			::= { hmWanMbusC6 22 }

hmWanMbusC6Value08		OBJECT-TYPE
			SYNTAX	INTEGER
			MAX-ACCESS	read-only
			STATUS	current
			::= { hmWanMbusC6 23 }

hmWanMbusC6VIF09		OBJECT-TYPE
			SYNTAX	INTEGER
			MAX-ACCESS	read-only
			STATUS	current
			::= { hmWanMbusC6 24 }

hmWanMbusC6Value09		OBJECT-TYPE
			SYNTAX	INTEGER
			MAX-ACCESS	read-only
			STATUS	current
			::= { hmWanMbusC6 25 }

hmWanMbusC6VIF0A		OBJECT-TYPE
			SYNTAX	INTEGER
			MAX-ACCESS	read-only
			STATUS	current
			::= { hmWanMbusC6 26 }

hmWanMbusC6Value0A		OBJECT-TYPE
			SYNTAX	INTEGER
			MAX-ACCESS	read-only
			STATUS	current
			::= { hmWanMbusC6 27 }

hmWanMbusC6VIF0B		OBJECT-TYPE
			SYNTAX	INTEGER
			MAX-ACCESS	read-only
			STATUS	current
			::= { hmWanMbusC6 28 }

hmWanMbusC6Value0B		OBJECT-TYPE
			SYNTAX	INTEGER
			MAX-ACCESS	read-only
			STATUS	current
			::= { hmWanMbusC6 29 }

hmWanMbusC6VIF0C		OBJECT-TYPE
			SYNTAX	INTEGER
			MAX-ACCESS	read-only
			STATUS	current
			::= { hmWanMbusC6 30 }

hmWanMbusC6Value0C		OBJECT-TYPE
			SYNTAX	INTEGER
			MAX-ACCESS	read-only
			STATUS	current
			::= { hmWanMbusC6 31 }

hmWanMbusC6VIF0D		OBJECT-TYPE
			SYNTAX	INTEGER
			MAX-ACCESS	read-only
			STATUS	current
			::= { hmWanMbusC6 32 }

hmWanMbusC6Value0D		OBJECT-TYPE
			SYNTAX	INTEGER
			MAX-ACCESS	read-only
			STATUS	current
			::= { hmWanMbusC6 33 }

hmWanMbusC6VIF0E		OBJECT-TYPE
			SYNTAX	INTEGER
			MAX-ACCESS	read-only
			STATUS	current
			::= { hmWanMbusC6 34 }

hmWanMbusC6Value0E		OBJECT-TYPE
			SYNTAX	INTEGER
			MAX-ACCESS	read-only
			STATUS	current
			::= { hmWanMbusC6 35 }

hmWanMbusC6VIF0F		OBJECT-TYPE
			SYNTAX	INTEGER
			MAX-ACCESS	read-only
			STATUS	current
			::= { hmWanMbusC6 36 }

hmWanMbusC6Value0F		OBJECT-TYPE
			SYNTAX	INTEGER
			MAX-ACCESS	read-only
			STATUS	current
			::= { hmWanMbusC6 37 }

hmWanMbusC6VIF10		OBJECT-TYPE
			SYNTAX	INTEGER
			MAX-ACCESS	read-only
			STATUS	current
			::= { hmWanMbusC6 38 }

hmWanMbusC6Value10		OBJECT-TYPE
			SYNTAX	INTEGER
			MAX-ACCESS	read-only
			STATUS	current
			::= { hmWanMbusC6 39 }

hmWanMbusC6VIF11		OBJECT-TYPE
			SYNTAX	INTEGER
			MAX-ACCESS	read-only
			STATUS	current
			::= { hmWanMbusC6 40 }

hmWanMbusC6Value11		OBJECT-TYPE
			SYNTAX	INTEGER
			MAX-ACCESS	read-only
			STATUS	current
			::= { hmWanMbusC6 41 }

hmWanMbusC6VIF12		OBJECT-TYPE
			SYNTAX	INTEGER
			MAX-ACCESS	read-only
			STATUS	current
			::= { hmWanMbusC6 42 }

hmWanMbusC6Value12		OBJECT-TYPE
			SYNTAX	INTEGER
			MAX-ACCESS	read-only
			STATUS	current
			::= { hmWanMbusC6 43 }

hmWanMbusC6VIF13		OBJECT-TYPE
			SYNTAX	INTEGER
			MAX-ACCESS	read-only
			STATUS	current
			::= { hmWanMbusC6 44 }

hmWanMbusC6Value13		OBJECT-TYPE
			SYNTAX	INTEGER
			MAX-ACCESS	read-only
			STATUS	current
			::= { hmWanMbusC6 45 }

hmWanMbusC6VIF14		OBJECT-TYPE
			SYNTAX	INTEGER
			MAX-ACCESS	read-only
			STATUS	current
			::= { hmWanMbusC6 46 }

hmWanMbusC6Value14		OBJECT-TYPE
			SYNTAX	INTEGER
			MAX-ACCESS	read-only
			STATUS	current
			::= { hmWanMbusC6 47 }

hmWanMbusC6VIF15		OBJECT-TYPE
			SYNTAX	INTEGER
			MAX-ACCESS	read-only
			STATUS	current
			::= { hmWanMbusC6 48 }

hmWanMbusC6Value15		OBJECT-TYPE
			SYNTAX	INTEGER
			MAX-ACCESS	read-only
			STATUS	current
			::= { hmWanMbusC6 49 }

hmWanMbusC6VIF16		OBJECT-TYPE
			SYNTAX	INTEGER
			MAX-ACCESS	read-only
			STATUS	current
			::= { hmWanMbusC6 50 }

hmWanMbusC6Value16		OBJECT-TYPE
			SYNTAX	INTEGER
			MAX-ACCESS	read-only
			STATUS	current
			::= { hmWanMbusC6 51 }

hmWanMbusC6VIF17		OBJECT-TYPE
			SYNTAX	INTEGER
			MAX-ACCESS	read-only
			STATUS	current
			::= { hmWanMbusC6 52 }

hmWanMbusC6Value17		OBJECT-TYPE
			SYNTAX	INTEGER
			MAX-ACCESS	read-only
			STATUS	current
			::= { hmWanMbusC6 53 }

hmWanMbusC6VIF18		OBJECT-TYPE
			SYNTAX	INTEGER
			MAX-ACCESS	read-only
			STATUS	current
			::= { hmWanMbusC6 54 }

hmWanMbusC6Value18		OBJECT-TYPE
			SYNTAX	INTEGER
			MAX-ACCESS	read-only
			STATUS	current
			::= { hmWanMbusC6 55 }

hmWanMbusC6VIF19		OBJECT-TYPE
			SYNTAX	INTEGER
			MAX-ACCESS	read-only
			STATUS	current
			::= { hmWanMbusC6 56 }

hmWanMbusC6Value19		OBJECT-TYPE
			SYNTAX	INTEGER
			MAX-ACCESS	read-only
			STATUS	current
			::= { hmWanMbusC6 57 }

hmWanMbusC6VIF1A		OBJECT-TYPE
			SYNTAX	INTEGER
			MAX-ACCESS	read-only
			STATUS	current
			::= { hmWanMbusC6 58 }

hmWanMbusC6Value1A		OBJECT-TYPE
			SYNTAX	INTEGER
			MAX-ACCESS	read-only
			STATUS	current
			::= { hmWanMbusC6 59 }

hmWanMbusC6VIF1B		OBJECT-TYPE
			SYNTAX	INTEGER
			MAX-ACCESS	read-only
			STATUS	current
			::= { hmWanMbusC6 60 }

hmWanMbusC6Value1B		OBJECT-TYPE
			SYNTAX	INTEGER
			MAX-ACCESS	read-only
			STATUS	current
			::= { hmWanMbusC6 61 }

hmWanMbusC6VIF1C		OBJECT-TYPE
			SYNTAX	INTEGER
			MAX-ACCESS	read-only
			STATUS	current
			::= { hmWanMbusC6 62 }

hmWanMbusC6Value1C		OBJECT-TYPE
			SYNTAX	INTEGER
			MAX-ACCESS	read-only
			STATUS	current
			::= { hmWanMbusC6 63 }

hmWanMbusC6VIF1D		OBJECT-TYPE
			SYNTAX	INTEGER
			MAX-ACCESS	read-only
			STATUS	current
			::= { hmWanMbusC6 64 }

hmWanMbusC6Value1D		OBJECT-TYPE
			SYNTAX	INTEGER
			MAX-ACCESS	read-only
			STATUS	current
			::= { hmWanMbusC6 65 }

hmWanMbusC6VIF1E		OBJECT-TYPE
			SYNTAX	INTEGER
			MAX-ACCESS	read-only
			STATUS	current
			::= { hmWanMbusC6 66 }

hmWanMbusC6Value1E		OBJECT-TYPE
			SYNTAX	INTEGER
			MAX-ACCESS	read-only
			STATUS	current
			::= { hmWanMbusC6 67 }

hmWanMbusC6VIF1F		OBJECT-TYPE
			SYNTAX	INTEGER
			MAX-ACCESS	read-only
			STATUS	current
			::= { hmWanMbusC6 68 }

hmWanMbusC6Value1F		OBJECT-TYPE
			SYNTAX	INTEGER
			MAX-ACCESS	read-only
			STATUS	current
			::= { hmWanMbusC6 69 }

hmWanMbusC6VIF20		OBJECT-TYPE
			SYNTAX	INTEGER
			MAX-ACCESS	read-only
			STATUS	current
			::= { hmWanMbusC6 70 }

hmWanMbusC6Value20		OBJECT-TYPE
			SYNTAX	INTEGER
			MAX-ACCESS	read-only
			STATUS	current
			::= { hmWanMbusC6 71 }

hmWanMbusC6VIF21		OBJECT-TYPE
			SYNTAX	INTEGER
			MAX-ACCESS	read-only
			STATUS	current
			::= { hmWanMbusC6 72 }

hmWanMbusC6Value21		OBJECT-TYPE
			SYNTAX	INTEGER
			MAX-ACCESS	read-only
			STATUS	current
			::= { hmWanMbusC6 73 }

hmWanMbusC6VIF22		OBJECT-TYPE
			SYNTAX	INTEGER
			MAX-ACCESS	read-only
			STATUS	current
			::= { hmWanMbusC6 74 }

hmWanMbusC6Value22		OBJECT-TYPE
			SYNTAX	INTEGER
			MAX-ACCESS	read-only
			STATUS	current
			::= { hmWanMbusC6 75 }

hmWanMbusC6VIF23		OBJECT-TYPE
			SYNTAX	INTEGER
			MAX-ACCESS	read-only
			STATUS	current
			::= { hmWanMbusC6 76 }

hmWanMbusC6Value23		OBJECT-TYPE
			SYNTAX	INTEGER
			MAX-ACCESS	read-only
			STATUS	current
			::= { hmWanMbusC6 77 }

hmWanMbusC6VIF24		OBJECT-TYPE
			SYNTAX	INTEGER
			MAX-ACCESS	read-only
			STATUS	current
			::= { hmWanMbusC6 78 }

hmWanMbusC6Value24		OBJECT-TYPE
			SYNTAX	INTEGER
			MAX-ACCESS	read-only
			STATUS	current
			::= { hmWanMbusC6 79 }

hmWanMbusC6VIF25		OBJECT-TYPE
			SYNTAX	INTEGER
			MAX-ACCESS	read-only
			STATUS	current
			::= { hmWanMbusC6 80 }

hmWanMbusC6Value25		OBJECT-TYPE
			SYNTAX	INTEGER
			MAX-ACCESS	read-only
			STATUS	current
			::= { hmWanMbusC6 81 }

hmWanMbusC6VIF26		OBJECT-TYPE
			SYNTAX	INTEGER
			MAX-ACCESS	read-only
			STATUS	current
			::= { hmWanMbusC6 82 }

hmWanMbusC6Value26		OBJECT-TYPE
			SYNTAX	INTEGER
			MAX-ACCESS	read-only
			STATUS	current
			::= { hmWanMbusC6 83 }

hmWanMbusC6VIF27		OBJECT-TYPE
			SYNTAX	INTEGER
			MAX-ACCESS	read-only
			STATUS	current
			::= { hmWanMbusC6 84 }

hmWanMbusC6Value27		OBJECT-TYPE
			SYNTAX	INTEGER
			MAX-ACCESS	read-only
			STATUS	current
			::= { hmWanMbusC6 85 }

hmWanMbusC6VIF28		OBJECT-TYPE
			SYNTAX	INTEGER
			MAX-ACCESS	read-only
			STATUS	current
			::= { hmWanMbusC6 86 }

hmWanMbusC6Value28		OBJECT-TYPE
			SYNTAX	INTEGER
			MAX-ACCESS	read-only
			STATUS	current
			::= { hmWanMbusC6 87 }

hmWanMbusC6VIF29		OBJECT-TYPE
			SYNTAX	INTEGER
			MAX-ACCESS	read-only
			STATUS	current
			::= { hmWanMbusC6 88 }

hmWanMbusC6Value29		OBJECT-TYPE
			SYNTAX	INTEGER
			MAX-ACCESS	read-only
			STATUS	current
			::= { hmWanMbusC6 89 }

hmWanMbusC6VIF2A		OBJECT-TYPE
			SYNTAX	INTEGER
			MAX-ACCESS	read-only
			STATUS	current
			::= { hmWanMbusC6 90 }

hmWanMbusC6Value2A		OBJECT-TYPE
			SYNTAX	INTEGER
			MAX-ACCESS	read-only
			STATUS	current
			::= { hmWanMbusC6 91 }

hmWanMbusC6VIF2B		OBJECT-TYPE
			SYNTAX	INTEGER
			MAX-ACCESS	read-only
			STATUS	current
			::= { hmWanMbusC6 92 }

hmWanMbusC6Value2B		OBJECT-TYPE
			SYNTAX	INTEGER
			MAX-ACCESS	read-only
			STATUS	current
			::= { hmWanMbusC6 93 }

hmWanMbusC6VIF2C		OBJECT-TYPE
			SYNTAX	INTEGER
			MAX-ACCESS	read-only
			STATUS	current
			::= { hmWanMbusC6 94 }

hmWanMbusC6Value2C		OBJECT-TYPE
			SYNTAX	INTEGER
			MAX-ACCESS	read-only
			STATUS	current
			::= { hmWanMbusC6 95 }

hmWanMbusC6VIF2D		OBJECT-TYPE
			SYNTAX	INTEGER
			MAX-ACCESS	read-only
			STATUS	current
			::= { hmWanMbusC6 96 }

hmWanMbusC6Value2D		OBJECT-TYPE
			SYNTAX	INTEGER
			MAX-ACCESS	read-only
			STATUS	current
			::= { hmWanMbusC6 97 }

hmWanMbusC6VIF2E		OBJECT-TYPE
			SYNTAX	INTEGER
			MAX-ACCESS	read-only
			STATUS	current
			::= { hmWanMbusC6 98 }

hmWanMbusC6Value2E		OBJECT-TYPE
			SYNTAX	INTEGER
			MAX-ACCESS	read-only
			STATUS	current
			::= { hmWanMbusC6 99 }

hmWanMbusC6VIF2F		OBJECT-TYPE
			SYNTAX	INTEGER
			MAX-ACCESS	read-only
			STATUS	current
			::= { hmWanMbusC6 100 }

hmWanMbusC6Value2F		OBJECT-TYPE
			SYNTAX	INTEGER
			MAX-ACCESS	read-only
			STATUS	current
			::= { hmWanMbusC6 101 }

hmWanMbusC7			OBJECT IDENTIFIER ::= { hmWanMbus 199 }

hmWanMbusC7IdNumber		OBJECT-TYPE
			SYNTAX	Gauge32
			MAX-ACCESS	read-only
			STATUS	current
			::= { hmWanMbusC7 1 }

hmWanMbusC7Manufacturer	OBJECT-TYPE
			SYNTAX	Gauge32
			MAX-ACCESS	read-only
			STATUS	current
			::= { hmWanMbusC7 2 }

hmWanMbusC7Version		OBJECT-TYPE
			SYNTAX	Gauge32
			MAX-ACCESS	read-only
			STATUS	current
			::= { hmWanMbusC7 3 }

hmWanMbusC7Medium		OBJECT-TYPE
			SYNTAX	Gauge32
			MAX-ACCESS	read-only
			STATUS	current
			::= { hmWanMbusC7 4 }

hmWanMbusC7Status		OBJECT-TYPE
			SYNTAX	Gauge32
			MAX-ACCESS	read-only
			STATUS	current
			::= { hmWanMbusC7 5 }

hmWanMbusC7VIF00		OBJECT-TYPE
			SYNTAX	INTEGER
			MAX-ACCESS	read-only
			STATUS	current
			::= { hmWanMbusC7 6 }

hmWanMbusC7Value00		OBJECT-TYPE
			SYNTAX	INTEGER
			MAX-ACCESS	read-only
			STATUS	current
			::= { hmWanMbusC7 7 }

hmWanMbusC7VIF01		OBJECT-TYPE
			SYNTAX	INTEGER
			MAX-ACCESS	read-only
			STATUS	current
			::= { hmWanMbusC7 8 }

hmWanMbusC7Value01		OBJECT-TYPE
			SYNTAX	INTEGER
			MAX-ACCESS	read-only
			STATUS	current
			::= { hmWanMbusC7 9 }

hmWanMbusC7VIF02		OBJECT-TYPE
			SYNTAX	INTEGER
			MAX-ACCESS	read-only
			STATUS	current
			::= { hmWanMbusC7 10 }

hmWanMbusC7Value02		OBJECT-TYPE
			SYNTAX	INTEGER
			MAX-ACCESS	read-only
			STATUS	current
			::= { hmWanMbusC7 11 }

hmWanMbusC7VIF03		OBJECT-TYPE
			SYNTAX	INTEGER
			MAX-ACCESS	read-only
			STATUS	current
			::= { hmWanMbusC7 12 }

hmWanMbusC7Value03		OBJECT-TYPE
			SYNTAX	INTEGER
			MAX-ACCESS	read-only
			STATUS	current
			::= { hmWanMbusC7 13 }

hmWanMbusC7VIF04		OBJECT-TYPE
			SYNTAX	INTEGER
			MAX-ACCESS	read-only
			STATUS	current
			::= { hmWanMbusC7 14 }

hmWanMbusC7Value04		OBJECT-TYPE
			SYNTAX	INTEGER
			MAX-ACCESS	read-only
			STATUS	current
			::= { hmWanMbusC7 15 }

hmWanMbusC7VIF05		OBJECT-TYPE
			SYNTAX	INTEGER
			MAX-ACCESS	read-only
			STATUS	current
			::= { hmWanMbusC7 16 }

hmWanMbusC7Value05		OBJECT-TYPE
			SYNTAX	INTEGER
			MAX-ACCESS	read-only
			STATUS	current
			::= { hmWanMbusC7 17 }

hmWanMbusC7VIF06		OBJECT-TYPE
			SYNTAX	INTEGER
			MAX-ACCESS	read-only
			STATUS	current
			::= { hmWanMbusC7 18 }

hmWanMbusC7Value06		OBJECT-TYPE
			SYNTAX	INTEGER
			MAX-ACCESS	read-only
			STATUS	current
			::= { hmWanMbusC7 19 }

hmWanMbusC7VIF07		OBJECT-TYPE
			SYNTAX	INTEGER
			MAX-ACCESS	read-only
			STATUS	current
			::= { hmWanMbusC7 20 }

hmWanMbusC7Value07		OBJECT-TYPE
			SYNTAX	INTEGER
			MAX-ACCESS	read-only
			STATUS	current
			::= { hmWanMbusC7 21 }

hmWanMbusC7VIF08		OBJECT-TYPE
			SYNTAX	INTEGER
			MAX-ACCESS	read-only
			STATUS	current
			::= { hmWanMbusC7 22 }

hmWanMbusC7Value08		OBJECT-TYPE
			SYNTAX	INTEGER
			MAX-ACCESS	read-only
			STATUS	current
			::= { hmWanMbusC7 23 }

hmWanMbusC7VIF09		OBJECT-TYPE
			SYNTAX	INTEGER
			MAX-ACCESS	read-only
			STATUS	current
			::= { hmWanMbusC7 24 }

hmWanMbusC7Value09		OBJECT-TYPE
			SYNTAX	INTEGER
			MAX-ACCESS	read-only
			STATUS	current
			::= { hmWanMbusC7 25 }

hmWanMbusC7VIF0A		OBJECT-TYPE
			SYNTAX	INTEGER
			MAX-ACCESS	read-only
			STATUS	current
			::= { hmWanMbusC7 26 }

hmWanMbusC7Value0A		OBJECT-TYPE
			SYNTAX	INTEGER
			MAX-ACCESS	read-only
			STATUS	current
			::= { hmWanMbusC7 27 }

hmWanMbusC7VIF0B		OBJECT-TYPE
			SYNTAX	INTEGER
			MAX-ACCESS	read-only
			STATUS	current
			::= { hmWanMbusC7 28 }

hmWanMbusC7Value0B		OBJECT-TYPE
			SYNTAX	INTEGER
			MAX-ACCESS	read-only
			STATUS	current
			::= { hmWanMbusC7 29 }

hmWanMbusC7VIF0C		OBJECT-TYPE
			SYNTAX	INTEGER
			MAX-ACCESS	read-only
			STATUS	current
			::= { hmWanMbusC7 30 }

hmWanMbusC7Value0C		OBJECT-TYPE
			SYNTAX	INTEGER
			MAX-ACCESS	read-only
			STATUS	current
			::= { hmWanMbusC7 31 }

hmWanMbusC7VIF0D		OBJECT-TYPE
			SYNTAX	INTEGER
			MAX-ACCESS	read-only
			STATUS	current
			::= { hmWanMbusC7 32 }

hmWanMbusC7Value0D		OBJECT-TYPE
			SYNTAX	INTEGER
			MAX-ACCESS	read-only
			STATUS	current
			::= { hmWanMbusC7 33 }

hmWanMbusC7VIF0E		OBJECT-TYPE
			SYNTAX	INTEGER
			MAX-ACCESS	read-only
			STATUS	current
			::= { hmWanMbusC7 34 }

hmWanMbusC7Value0E		OBJECT-TYPE
			SYNTAX	INTEGER
			MAX-ACCESS	read-only
			STATUS	current
			::= { hmWanMbusC7 35 }

hmWanMbusC7VIF0F		OBJECT-TYPE
			SYNTAX	INTEGER
			MAX-ACCESS	read-only
			STATUS	current
			::= { hmWanMbusC7 36 }

hmWanMbusC7Value0F		OBJECT-TYPE
			SYNTAX	INTEGER
			MAX-ACCESS	read-only
			STATUS	current
			::= { hmWanMbusC7 37 }

hmWanMbusC7VIF10		OBJECT-TYPE
			SYNTAX	INTEGER
			MAX-ACCESS	read-only
			STATUS	current
			::= { hmWanMbusC7 38 }

hmWanMbusC7Value10		OBJECT-TYPE
			SYNTAX	INTEGER
			MAX-ACCESS	read-only
			STATUS	current
			::= { hmWanMbusC7 39 }

hmWanMbusC7VIF11		OBJECT-TYPE
			SYNTAX	INTEGER
			MAX-ACCESS	read-only
			STATUS	current
			::= { hmWanMbusC7 40 }

hmWanMbusC7Value11		OBJECT-TYPE
			SYNTAX	INTEGER
			MAX-ACCESS	read-only
			STATUS	current
			::= { hmWanMbusC7 41 }

hmWanMbusC7VIF12		OBJECT-TYPE
			SYNTAX	INTEGER
			MAX-ACCESS	read-only
			STATUS	current
			::= { hmWanMbusC7 42 }

hmWanMbusC7Value12		OBJECT-TYPE
			SYNTAX	INTEGER
			MAX-ACCESS	read-only
			STATUS	current
			::= { hmWanMbusC7 43 }

hmWanMbusC7VIF13		OBJECT-TYPE
			SYNTAX	INTEGER
			MAX-ACCESS	read-only
			STATUS	current
			::= { hmWanMbusC7 44 }

hmWanMbusC7Value13		OBJECT-TYPE
			SYNTAX	INTEGER
			MAX-ACCESS	read-only
			STATUS	current
			::= { hmWanMbusC7 45 }

hmWanMbusC7VIF14		OBJECT-TYPE
			SYNTAX	INTEGER
			MAX-ACCESS	read-only
			STATUS	current
			::= { hmWanMbusC7 46 }

hmWanMbusC7Value14		OBJECT-TYPE
			SYNTAX	INTEGER
			MAX-ACCESS	read-only
			STATUS	current
			::= { hmWanMbusC7 47 }

hmWanMbusC7VIF15		OBJECT-TYPE
			SYNTAX	INTEGER
			MAX-ACCESS	read-only
			STATUS	current
			::= { hmWanMbusC7 48 }

hmWanMbusC7Value15		OBJECT-TYPE
			SYNTAX	INTEGER
			MAX-ACCESS	read-only
			STATUS	current
			::= { hmWanMbusC7 49 }

hmWanMbusC7VIF16		OBJECT-TYPE
			SYNTAX	INTEGER
			MAX-ACCESS	read-only
			STATUS	current
			::= { hmWanMbusC7 50 }

hmWanMbusC7Value16		OBJECT-TYPE
			SYNTAX	INTEGER
			MAX-ACCESS	read-only
			STATUS	current
			::= { hmWanMbusC7 51 }

hmWanMbusC7VIF17		OBJECT-TYPE
			SYNTAX	INTEGER
			MAX-ACCESS	read-only
			STATUS	current
			::= { hmWanMbusC7 52 }

hmWanMbusC7Value17		OBJECT-TYPE
			SYNTAX	INTEGER
			MAX-ACCESS	read-only
			STATUS	current
			::= { hmWanMbusC7 53 }

hmWanMbusC7VIF18		OBJECT-TYPE
			SYNTAX	INTEGER
			MAX-ACCESS	read-only
			STATUS	current
			::= { hmWanMbusC7 54 }

hmWanMbusC7Value18		OBJECT-TYPE
			SYNTAX	INTEGER
			MAX-ACCESS	read-only
			STATUS	current
			::= { hmWanMbusC7 55 }

hmWanMbusC7VIF19		OBJECT-TYPE
			SYNTAX	INTEGER
			MAX-ACCESS	read-only
			STATUS	current
			::= { hmWanMbusC7 56 }

hmWanMbusC7Value19		OBJECT-TYPE
			SYNTAX	INTEGER
			MAX-ACCESS	read-only
			STATUS	current
			::= { hmWanMbusC7 57 }

hmWanMbusC7VIF1A		OBJECT-TYPE
			SYNTAX	INTEGER
			MAX-ACCESS	read-only
			STATUS	current
			::= { hmWanMbusC7 58 }

hmWanMbusC7Value1A		OBJECT-TYPE
			SYNTAX	INTEGER
			MAX-ACCESS	read-only
			STATUS	current
			::= { hmWanMbusC7 59 }

hmWanMbusC7VIF1B		OBJECT-TYPE
			SYNTAX	INTEGER
			MAX-ACCESS	read-only
			STATUS	current
			::= { hmWanMbusC7 60 }

hmWanMbusC7Value1B		OBJECT-TYPE
			SYNTAX	INTEGER
			MAX-ACCESS	read-only
			STATUS	current
			::= { hmWanMbusC7 61 }

hmWanMbusC7VIF1C		OBJECT-TYPE
			SYNTAX	INTEGER
			MAX-ACCESS	read-only
			STATUS	current
			::= { hmWanMbusC7 62 }

hmWanMbusC7Value1C		OBJECT-TYPE
			SYNTAX	INTEGER
			MAX-ACCESS	read-only
			STATUS	current
			::= { hmWanMbusC7 63 }

hmWanMbusC7VIF1D		OBJECT-TYPE
			SYNTAX	INTEGER
			MAX-ACCESS	read-only
			STATUS	current
			::= { hmWanMbusC7 64 }

hmWanMbusC7Value1D		OBJECT-TYPE
			SYNTAX	INTEGER
			MAX-ACCESS	read-only
			STATUS	current
			::= { hmWanMbusC7 65 }

hmWanMbusC7VIF1E		OBJECT-TYPE
			SYNTAX	INTEGER
			MAX-ACCESS	read-only
			STATUS	current
			::= { hmWanMbusC7 66 }

hmWanMbusC7Value1E		OBJECT-TYPE
			SYNTAX	INTEGER
			MAX-ACCESS	read-only
			STATUS	current
			::= { hmWanMbusC7 67 }

hmWanMbusC7VIF1F		OBJECT-TYPE
			SYNTAX	INTEGER
			MAX-ACCESS	read-only
			STATUS	current
			::= { hmWanMbusC7 68 }

hmWanMbusC7Value1F		OBJECT-TYPE
			SYNTAX	INTEGER
			MAX-ACCESS	read-only
			STATUS	current
			::= { hmWanMbusC7 69 }

hmWanMbusC7VIF20		OBJECT-TYPE
			SYNTAX	INTEGER
			MAX-ACCESS	read-only
			STATUS	current
			::= { hmWanMbusC7 70 }

hmWanMbusC7Value20		OBJECT-TYPE
			SYNTAX	INTEGER
			MAX-ACCESS	read-only
			STATUS	current
			::= { hmWanMbusC7 71 }

hmWanMbusC7VIF21		OBJECT-TYPE
			SYNTAX	INTEGER
			MAX-ACCESS	read-only
			STATUS	current
			::= { hmWanMbusC7 72 }

hmWanMbusC7Value21		OBJECT-TYPE
			SYNTAX	INTEGER
			MAX-ACCESS	read-only
			STATUS	current
			::= { hmWanMbusC7 73 }

hmWanMbusC7VIF22		OBJECT-TYPE
			SYNTAX	INTEGER
			MAX-ACCESS	read-only
			STATUS	current
			::= { hmWanMbusC7 74 }

hmWanMbusC7Value22		OBJECT-TYPE
			SYNTAX	INTEGER
			MAX-ACCESS	read-only
			STATUS	current
			::= { hmWanMbusC7 75 }

hmWanMbusC7VIF23		OBJECT-TYPE
			SYNTAX	INTEGER
			MAX-ACCESS	read-only
			STATUS	current
			::= { hmWanMbusC7 76 }

hmWanMbusC7Value23		OBJECT-TYPE
			SYNTAX	INTEGER
			MAX-ACCESS	read-only
			STATUS	current
			::= { hmWanMbusC7 77 }

hmWanMbusC7VIF24		OBJECT-TYPE
			SYNTAX	INTEGER
			MAX-ACCESS	read-only
			STATUS	current
			::= { hmWanMbusC7 78 }

hmWanMbusC7Value24		OBJECT-TYPE
			SYNTAX	INTEGER
			MAX-ACCESS	read-only
			STATUS	current
			::= { hmWanMbusC7 79 }

hmWanMbusC7VIF25		OBJECT-TYPE
			SYNTAX	INTEGER
			MAX-ACCESS	read-only
			STATUS	current
			::= { hmWanMbusC7 80 }

hmWanMbusC7Value25		OBJECT-TYPE
			SYNTAX	INTEGER
			MAX-ACCESS	read-only
			STATUS	current
			::= { hmWanMbusC7 81 }

hmWanMbusC7VIF26		OBJECT-TYPE
			SYNTAX	INTEGER
			MAX-ACCESS	read-only
			STATUS	current
			::= { hmWanMbusC7 82 }

hmWanMbusC7Value26		OBJECT-TYPE
			SYNTAX	INTEGER
			MAX-ACCESS	read-only
			STATUS	current
			::= { hmWanMbusC7 83 }

hmWanMbusC7VIF27		OBJECT-TYPE
			SYNTAX	INTEGER
			MAX-ACCESS	read-only
			STATUS	current
			::= { hmWanMbusC7 84 }

hmWanMbusC7Value27		OBJECT-TYPE
			SYNTAX	INTEGER
			MAX-ACCESS	read-only
			STATUS	current
			::= { hmWanMbusC7 85 }

hmWanMbusC7VIF28		OBJECT-TYPE
			SYNTAX	INTEGER
			MAX-ACCESS	read-only
			STATUS	current
			::= { hmWanMbusC7 86 }

hmWanMbusC7Value28		OBJECT-TYPE
			SYNTAX	INTEGER
			MAX-ACCESS	read-only
			STATUS	current
			::= { hmWanMbusC7 87 }

hmWanMbusC7VIF29		OBJECT-TYPE
			SYNTAX	INTEGER
			MAX-ACCESS	read-only
			STATUS	current
			::= { hmWanMbusC7 88 }

hmWanMbusC7Value29		OBJECT-TYPE
			SYNTAX	INTEGER
			MAX-ACCESS	read-only
			STATUS	current
			::= { hmWanMbusC7 89 }

hmWanMbusC7VIF2A		OBJECT-TYPE
			SYNTAX	INTEGER
			MAX-ACCESS	read-only
			STATUS	current
			::= { hmWanMbusC7 90 }

hmWanMbusC7Value2A		OBJECT-TYPE
			SYNTAX	INTEGER
			MAX-ACCESS	read-only
			STATUS	current
			::= { hmWanMbusC7 91 }

hmWanMbusC7VIF2B		OBJECT-TYPE
			SYNTAX	INTEGER
			MAX-ACCESS	read-only
			STATUS	current
			::= { hmWanMbusC7 92 }

hmWanMbusC7Value2B		OBJECT-TYPE
			SYNTAX	INTEGER
			MAX-ACCESS	read-only
			STATUS	current
			::= { hmWanMbusC7 93 }

hmWanMbusC7VIF2C		OBJECT-TYPE
			SYNTAX	INTEGER
			MAX-ACCESS	read-only
			STATUS	current
			::= { hmWanMbusC7 94 }

hmWanMbusC7Value2C		OBJECT-TYPE
			SYNTAX	INTEGER
			MAX-ACCESS	read-only
			STATUS	current
			::= { hmWanMbusC7 95 }

hmWanMbusC7VIF2D		OBJECT-TYPE
			SYNTAX	INTEGER
			MAX-ACCESS	read-only
			STATUS	current
			::= { hmWanMbusC7 96 }

hmWanMbusC7Value2D		OBJECT-TYPE
			SYNTAX	INTEGER
			MAX-ACCESS	read-only
			STATUS	current
			::= { hmWanMbusC7 97 }

hmWanMbusC7VIF2E		OBJECT-TYPE
			SYNTAX	INTEGER
			MAX-ACCESS	read-only
			STATUS	current
			::= { hmWanMbusC7 98 }

hmWanMbusC7Value2E		OBJECT-TYPE
			SYNTAX	INTEGER
			MAX-ACCESS	read-only
			STATUS	current
			::= { hmWanMbusC7 99 }

hmWanMbusC7VIF2F		OBJECT-TYPE
			SYNTAX	INTEGER
			MAX-ACCESS	read-only
			STATUS	current
			::= { hmWanMbusC7 100 }

hmWanMbusC7Value2F		OBJECT-TYPE
			SYNTAX	INTEGER
			MAX-ACCESS	read-only
			STATUS	current
			::= { hmWanMbusC7 101 }

hmWanMbusC8			OBJECT IDENTIFIER ::= { hmWanMbus 200 }

hmWanMbusC8IdNumber		OBJECT-TYPE
			SYNTAX	Gauge32
			MAX-ACCESS	read-only
			STATUS	current
			::= { hmWanMbusC8 1 }

hmWanMbusC8Manufacturer	OBJECT-TYPE
			SYNTAX	Gauge32
			MAX-ACCESS	read-only
			STATUS	current
			::= { hmWanMbusC8 2 }

hmWanMbusC8Version		OBJECT-TYPE
			SYNTAX	Gauge32
			MAX-ACCESS	read-only
			STATUS	current
			::= { hmWanMbusC8 3 }

hmWanMbusC8Medium		OBJECT-TYPE
			SYNTAX	Gauge32
			MAX-ACCESS	read-only
			STATUS	current
			::= { hmWanMbusC8 4 }

hmWanMbusC8Status		OBJECT-TYPE
			SYNTAX	Gauge32
			MAX-ACCESS	read-only
			STATUS	current
			::= { hmWanMbusC8 5 }

hmWanMbusC8VIF00		OBJECT-TYPE
			SYNTAX	INTEGER
			MAX-ACCESS	read-only
			STATUS	current
			::= { hmWanMbusC8 6 }

hmWanMbusC8Value00		OBJECT-TYPE
			SYNTAX	INTEGER
			MAX-ACCESS	read-only
			STATUS	current
			::= { hmWanMbusC8 7 }

hmWanMbusC8VIF01		OBJECT-TYPE
			SYNTAX	INTEGER
			MAX-ACCESS	read-only
			STATUS	current
			::= { hmWanMbusC8 8 }

hmWanMbusC8Value01		OBJECT-TYPE
			SYNTAX	INTEGER
			MAX-ACCESS	read-only
			STATUS	current
			::= { hmWanMbusC8 9 }

hmWanMbusC8VIF02		OBJECT-TYPE
			SYNTAX	INTEGER
			MAX-ACCESS	read-only
			STATUS	current
			::= { hmWanMbusC8 10 }

hmWanMbusC8Value02		OBJECT-TYPE
			SYNTAX	INTEGER
			MAX-ACCESS	read-only
			STATUS	current
			::= { hmWanMbusC8 11 }

hmWanMbusC8VIF03		OBJECT-TYPE
			SYNTAX	INTEGER
			MAX-ACCESS	read-only
			STATUS	current
			::= { hmWanMbusC8 12 }

hmWanMbusC8Value03		OBJECT-TYPE
			SYNTAX	INTEGER
			MAX-ACCESS	read-only
			STATUS	current
			::= { hmWanMbusC8 13 }

hmWanMbusC8VIF04		OBJECT-TYPE
			SYNTAX	INTEGER
			MAX-ACCESS	read-only
			STATUS	current
			::= { hmWanMbusC8 14 }

hmWanMbusC8Value04		OBJECT-TYPE
			SYNTAX	INTEGER
			MAX-ACCESS	read-only
			STATUS	current
			::= { hmWanMbusC8 15 }

hmWanMbusC8VIF05		OBJECT-TYPE
			SYNTAX	INTEGER
			MAX-ACCESS	read-only
			STATUS	current
			::= { hmWanMbusC8 16 }

hmWanMbusC8Value05		OBJECT-TYPE
			SYNTAX	INTEGER
			MAX-ACCESS	read-only
			STATUS	current
			::= { hmWanMbusC8 17 }

hmWanMbusC8VIF06		OBJECT-TYPE
			SYNTAX	INTEGER
			MAX-ACCESS	read-only
			STATUS	current
			::= { hmWanMbusC8 18 }

hmWanMbusC8Value06		OBJECT-TYPE
			SYNTAX	INTEGER
			MAX-ACCESS	read-only
			STATUS	current
			::= { hmWanMbusC8 19 }

hmWanMbusC8VIF07		OBJECT-TYPE
			SYNTAX	INTEGER
			MAX-ACCESS	read-only
			STATUS	current
			::= { hmWanMbusC8 20 }

hmWanMbusC8Value07		OBJECT-TYPE
			SYNTAX	INTEGER
			MAX-ACCESS	read-only
			STATUS	current
			::= { hmWanMbusC8 21 }

hmWanMbusC8VIF08		OBJECT-TYPE
			SYNTAX	INTEGER
			MAX-ACCESS	read-only
			STATUS	current
			::= { hmWanMbusC8 22 }

hmWanMbusC8Value08		OBJECT-TYPE
			SYNTAX	INTEGER
			MAX-ACCESS	read-only
			STATUS	current
			::= { hmWanMbusC8 23 }

hmWanMbusC8VIF09		OBJECT-TYPE
			SYNTAX	INTEGER
			MAX-ACCESS	read-only
			STATUS	current
			::= { hmWanMbusC8 24 }

hmWanMbusC8Value09		OBJECT-TYPE
			SYNTAX	INTEGER
			MAX-ACCESS	read-only
			STATUS	current
			::= { hmWanMbusC8 25 }

hmWanMbusC8VIF0A		OBJECT-TYPE
			SYNTAX	INTEGER
			MAX-ACCESS	read-only
			STATUS	current
			::= { hmWanMbusC8 26 }

hmWanMbusC8Value0A		OBJECT-TYPE
			SYNTAX	INTEGER
			MAX-ACCESS	read-only
			STATUS	current
			::= { hmWanMbusC8 27 }

hmWanMbusC8VIF0B		OBJECT-TYPE
			SYNTAX	INTEGER
			MAX-ACCESS	read-only
			STATUS	current
			::= { hmWanMbusC8 28 }

hmWanMbusC8Value0B		OBJECT-TYPE
			SYNTAX	INTEGER
			MAX-ACCESS	read-only
			STATUS	current
			::= { hmWanMbusC8 29 }

hmWanMbusC8VIF0C		OBJECT-TYPE
			SYNTAX	INTEGER
			MAX-ACCESS	read-only
			STATUS	current
			::= { hmWanMbusC8 30 }

hmWanMbusC8Value0C		OBJECT-TYPE
			SYNTAX	INTEGER
			MAX-ACCESS	read-only
			STATUS	current
			::= { hmWanMbusC8 31 }

hmWanMbusC8VIF0D		OBJECT-TYPE
			SYNTAX	INTEGER
			MAX-ACCESS	read-only
			STATUS	current
			::= { hmWanMbusC8 32 }

hmWanMbusC8Value0D		OBJECT-TYPE
			SYNTAX	INTEGER
			MAX-ACCESS	read-only
			STATUS	current
			::= { hmWanMbusC8 33 }

hmWanMbusC8VIF0E		OBJECT-TYPE
			SYNTAX	INTEGER
			MAX-ACCESS	read-only
			STATUS	current
			::= { hmWanMbusC8 34 }

hmWanMbusC8Value0E		OBJECT-TYPE
			SYNTAX	INTEGER
			MAX-ACCESS	read-only
			STATUS	current
			::= { hmWanMbusC8 35 }

hmWanMbusC8VIF0F		OBJECT-TYPE
			SYNTAX	INTEGER
			MAX-ACCESS	read-only
			STATUS	current
			::= { hmWanMbusC8 36 }

hmWanMbusC8Value0F		OBJECT-TYPE
			SYNTAX	INTEGER
			MAX-ACCESS	read-only
			STATUS	current
			::= { hmWanMbusC8 37 }

hmWanMbusC8VIF10		OBJECT-TYPE
			SYNTAX	INTEGER
			MAX-ACCESS	read-only
			STATUS	current
			::= { hmWanMbusC8 38 }

hmWanMbusC8Value10		OBJECT-TYPE
			SYNTAX	INTEGER
			MAX-ACCESS	read-only
			STATUS	current
			::= { hmWanMbusC8 39 }

hmWanMbusC8VIF11		OBJECT-TYPE
			SYNTAX	INTEGER
			MAX-ACCESS	read-only
			STATUS	current
			::= { hmWanMbusC8 40 }

hmWanMbusC8Value11		OBJECT-TYPE
			SYNTAX	INTEGER
			MAX-ACCESS	read-only
			STATUS	current
			::= { hmWanMbusC8 41 }

hmWanMbusC8VIF12		OBJECT-TYPE
			SYNTAX	INTEGER
			MAX-ACCESS	read-only
			STATUS	current
			::= { hmWanMbusC8 42 }

hmWanMbusC8Value12		OBJECT-TYPE
			SYNTAX	INTEGER
			MAX-ACCESS	read-only
			STATUS	current
			::= { hmWanMbusC8 43 }

hmWanMbusC8VIF13		OBJECT-TYPE
			SYNTAX	INTEGER
			MAX-ACCESS	read-only
			STATUS	current
			::= { hmWanMbusC8 44 }

hmWanMbusC8Value13		OBJECT-TYPE
			SYNTAX	INTEGER
			MAX-ACCESS	read-only
			STATUS	current
			::= { hmWanMbusC8 45 }

hmWanMbusC8VIF14		OBJECT-TYPE
			SYNTAX	INTEGER
			MAX-ACCESS	read-only
			STATUS	current
			::= { hmWanMbusC8 46 }

hmWanMbusC8Value14		OBJECT-TYPE
			SYNTAX	INTEGER
			MAX-ACCESS	read-only
			STATUS	current
			::= { hmWanMbusC8 47 }

hmWanMbusC8VIF15		OBJECT-TYPE
			SYNTAX	INTEGER
			MAX-ACCESS	read-only
			STATUS	current
			::= { hmWanMbusC8 48 }

hmWanMbusC8Value15		OBJECT-TYPE
			SYNTAX	INTEGER
			MAX-ACCESS	read-only
			STATUS	current
			::= { hmWanMbusC8 49 }

hmWanMbusC8VIF16		OBJECT-TYPE
			SYNTAX	INTEGER
			MAX-ACCESS	read-only
			STATUS	current
			::= { hmWanMbusC8 50 }

hmWanMbusC8Value16		OBJECT-TYPE
			SYNTAX	INTEGER
			MAX-ACCESS	read-only
			STATUS	current
			::= { hmWanMbusC8 51 }

hmWanMbusC8VIF17		OBJECT-TYPE
			SYNTAX	INTEGER
			MAX-ACCESS	read-only
			STATUS	current
			::= { hmWanMbusC8 52 }

hmWanMbusC8Value17		OBJECT-TYPE
			SYNTAX	INTEGER
			MAX-ACCESS	read-only
			STATUS	current
			::= { hmWanMbusC8 53 }

hmWanMbusC8VIF18		OBJECT-TYPE
			SYNTAX	INTEGER
			MAX-ACCESS	read-only
			STATUS	current
			::= { hmWanMbusC8 54 }

hmWanMbusC8Value18		OBJECT-TYPE
			SYNTAX	INTEGER
			MAX-ACCESS	read-only
			STATUS	current
			::= { hmWanMbusC8 55 }

hmWanMbusC8VIF19		OBJECT-TYPE
			SYNTAX	INTEGER
			MAX-ACCESS	read-only
			STATUS	current
			::= { hmWanMbusC8 56 }

hmWanMbusC8Value19		OBJECT-TYPE
			SYNTAX	INTEGER
			MAX-ACCESS	read-only
			STATUS	current
			::= { hmWanMbusC8 57 }

hmWanMbusC8VIF1A		OBJECT-TYPE
			SYNTAX	INTEGER
			MAX-ACCESS	read-only
			STATUS	current
			::= { hmWanMbusC8 58 }

hmWanMbusC8Value1A		OBJECT-TYPE
			SYNTAX	INTEGER
			MAX-ACCESS	read-only
			STATUS	current
			::= { hmWanMbusC8 59 }

hmWanMbusC8VIF1B		OBJECT-TYPE
			SYNTAX	INTEGER
			MAX-ACCESS	read-only
			STATUS	current
			::= { hmWanMbusC8 60 }

hmWanMbusC8Value1B		OBJECT-TYPE
			SYNTAX	INTEGER
			MAX-ACCESS	read-only
			STATUS	current
			::= { hmWanMbusC8 61 }

hmWanMbusC8VIF1C		OBJECT-TYPE
			SYNTAX	INTEGER
			MAX-ACCESS	read-only
			STATUS	current
			::= { hmWanMbusC8 62 }

hmWanMbusC8Value1C		OBJECT-TYPE
			SYNTAX	INTEGER
			MAX-ACCESS	read-only
			STATUS	current
			::= { hmWanMbusC8 63 }

hmWanMbusC8VIF1D		OBJECT-TYPE
			SYNTAX	INTEGER
			MAX-ACCESS	read-only
			STATUS	current
			::= { hmWanMbusC8 64 }

hmWanMbusC8Value1D		OBJECT-TYPE
			SYNTAX	INTEGER
			MAX-ACCESS	read-only
			STATUS	current
			::= { hmWanMbusC8 65 }

hmWanMbusC8VIF1E		OBJECT-TYPE
			SYNTAX	INTEGER
			MAX-ACCESS	read-only
			STATUS	current
			::= { hmWanMbusC8 66 }

hmWanMbusC8Value1E		OBJECT-TYPE
			SYNTAX	INTEGER
			MAX-ACCESS	read-only
			STATUS	current
			::= { hmWanMbusC8 67 }

hmWanMbusC8VIF1F		OBJECT-TYPE
			SYNTAX	INTEGER
			MAX-ACCESS	read-only
			STATUS	current
			::= { hmWanMbusC8 68 }

hmWanMbusC8Value1F		OBJECT-TYPE
			SYNTAX	INTEGER
			MAX-ACCESS	read-only
			STATUS	current
			::= { hmWanMbusC8 69 }

hmWanMbusC8VIF20		OBJECT-TYPE
			SYNTAX	INTEGER
			MAX-ACCESS	read-only
			STATUS	current
			::= { hmWanMbusC8 70 }

hmWanMbusC8Value20		OBJECT-TYPE
			SYNTAX	INTEGER
			MAX-ACCESS	read-only
			STATUS	current
			::= { hmWanMbusC8 71 }

hmWanMbusC8VIF21		OBJECT-TYPE
			SYNTAX	INTEGER
			MAX-ACCESS	read-only
			STATUS	current
			::= { hmWanMbusC8 72 }

hmWanMbusC8Value21		OBJECT-TYPE
			SYNTAX	INTEGER
			MAX-ACCESS	read-only
			STATUS	current
			::= { hmWanMbusC8 73 }

hmWanMbusC8VIF22		OBJECT-TYPE
			SYNTAX	INTEGER
			MAX-ACCESS	read-only
			STATUS	current
			::= { hmWanMbusC8 74 }

hmWanMbusC8Value22		OBJECT-TYPE
			SYNTAX	INTEGER
			MAX-ACCESS	read-only
			STATUS	current
			::= { hmWanMbusC8 75 }

hmWanMbusC8VIF23		OBJECT-TYPE
			SYNTAX	INTEGER
			MAX-ACCESS	read-only
			STATUS	current
			::= { hmWanMbusC8 76 }

hmWanMbusC8Value23		OBJECT-TYPE
			SYNTAX	INTEGER
			MAX-ACCESS	read-only
			STATUS	current
			::= { hmWanMbusC8 77 }

hmWanMbusC8VIF24		OBJECT-TYPE
			SYNTAX	INTEGER
			MAX-ACCESS	read-only
			STATUS	current
			::= { hmWanMbusC8 78 }

hmWanMbusC8Value24		OBJECT-TYPE
			SYNTAX	INTEGER
			MAX-ACCESS	read-only
			STATUS	current
			::= { hmWanMbusC8 79 }

hmWanMbusC8VIF25		OBJECT-TYPE
			SYNTAX	INTEGER
			MAX-ACCESS	read-only
			STATUS	current
			::= { hmWanMbusC8 80 }

hmWanMbusC8Value25		OBJECT-TYPE
			SYNTAX	INTEGER
			MAX-ACCESS	read-only
			STATUS	current
			::= { hmWanMbusC8 81 }

hmWanMbusC8VIF26		OBJECT-TYPE
			SYNTAX	INTEGER
			MAX-ACCESS	read-only
			STATUS	current
			::= { hmWanMbusC8 82 }

hmWanMbusC8Value26		OBJECT-TYPE
			SYNTAX	INTEGER
			MAX-ACCESS	read-only
			STATUS	current
			::= { hmWanMbusC8 83 }

hmWanMbusC8VIF27		OBJECT-TYPE
			SYNTAX	INTEGER
			MAX-ACCESS	read-only
			STATUS	current
			::= { hmWanMbusC8 84 }

hmWanMbusC8Value27		OBJECT-TYPE
			SYNTAX	INTEGER
			MAX-ACCESS	read-only
			STATUS	current
			::= { hmWanMbusC8 85 }

hmWanMbusC8VIF28		OBJECT-TYPE
			SYNTAX	INTEGER
			MAX-ACCESS	read-only
			STATUS	current
			::= { hmWanMbusC8 86 }

hmWanMbusC8Value28		OBJECT-TYPE
			SYNTAX	INTEGER
			MAX-ACCESS	read-only
			STATUS	current
			::= { hmWanMbusC8 87 }

hmWanMbusC8VIF29		OBJECT-TYPE
			SYNTAX	INTEGER
			MAX-ACCESS	read-only
			STATUS	current
			::= { hmWanMbusC8 88 }

hmWanMbusC8Value29		OBJECT-TYPE
			SYNTAX	INTEGER
			MAX-ACCESS	read-only
			STATUS	current
			::= { hmWanMbusC8 89 }

hmWanMbusC8VIF2A		OBJECT-TYPE
			SYNTAX	INTEGER
			MAX-ACCESS	read-only
			STATUS	current
			::= { hmWanMbusC8 90 }

hmWanMbusC8Value2A		OBJECT-TYPE
			SYNTAX	INTEGER
			MAX-ACCESS	read-only
			STATUS	current
			::= { hmWanMbusC8 91 }

hmWanMbusC8VIF2B		OBJECT-TYPE
			SYNTAX	INTEGER
			MAX-ACCESS	read-only
			STATUS	current
			::= { hmWanMbusC8 92 }

hmWanMbusC8Value2B		OBJECT-TYPE
			SYNTAX	INTEGER
			MAX-ACCESS	read-only
			STATUS	current
			::= { hmWanMbusC8 93 }

hmWanMbusC8VIF2C		OBJECT-TYPE
			SYNTAX	INTEGER
			MAX-ACCESS	read-only
			STATUS	current
			::= { hmWanMbusC8 94 }

hmWanMbusC8Value2C		OBJECT-TYPE
			SYNTAX	INTEGER
			MAX-ACCESS	read-only
			STATUS	current
			::= { hmWanMbusC8 95 }

hmWanMbusC8VIF2D		OBJECT-TYPE
			SYNTAX	INTEGER
			MAX-ACCESS	read-only
			STATUS	current
			::= { hmWanMbusC8 96 }

hmWanMbusC8Value2D		OBJECT-TYPE
			SYNTAX	INTEGER
			MAX-ACCESS	read-only
			STATUS	current
			::= { hmWanMbusC8 97 }

hmWanMbusC8VIF2E		OBJECT-TYPE
			SYNTAX	INTEGER
			MAX-ACCESS	read-only
			STATUS	current
			::= { hmWanMbusC8 98 }

hmWanMbusC8Value2E		OBJECT-TYPE
			SYNTAX	INTEGER
			MAX-ACCESS	read-only
			STATUS	current
			::= { hmWanMbusC8 99 }

hmWanMbusC8VIF2F		OBJECT-TYPE
			SYNTAX	INTEGER
			MAX-ACCESS	read-only
			STATUS	current
			::= { hmWanMbusC8 100 }

hmWanMbusC8Value2F		OBJECT-TYPE
			SYNTAX	INTEGER
			MAX-ACCESS	read-only
			STATUS	current
			::= { hmWanMbusC8 101 }

hmWanMbusC9			OBJECT IDENTIFIER ::= { hmWanMbus 201 }

hmWanMbusC9IdNumber		OBJECT-TYPE
			SYNTAX	Gauge32
			MAX-ACCESS	read-only
			STATUS	current
			::= { hmWanMbusC9 1 }

hmWanMbusC9Manufacturer	OBJECT-TYPE
			SYNTAX	Gauge32
			MAX-ACCESS	read-only
			STATUS	current
			::= { hmWanMbusC9 2 }

hmWanMbusC9Version		OBJECT-TYPE
			SYNTAX	Gauge32
			MAX-ACCESS	read-only
			STATUS	current
			::= { hmWanMbusC9 3 }

hmWanMbusC9Medium		OBJECT-TYPE
			SYNTAX	Gauge32
			MAX-ACCESS	read-only
			STATUS	current
			::= { hmWanMbusC9 4 }

hmWanMbusC9Status		OBJECT-TYPE
			SYNTAX	Gauge32
			MAX-ACCESS	read-only
			STATUS	current
			::= { hmWanMbusC9 5 }

hmWanMbusC9VIF00		OBJECT-TYPE
			SYNTAX	INTEGER
			MAX-ACCESS	read-only
			STATUS	current
			::= { hmWanMbusC9 6 }

hmWanMbusC9Value00		OBJECT-TYPE
			SYNTAX	INTEGER
			MAX-ACCESS	read-only
			STATUS	current
			::= { hmWanMbusC9 7 }

hmWanMbusC9VIF01		OBJECT-TYPE
			SYNTAX	INTEGER
			MAX-ACCESS	read-only
			STATUS	current
			::= { hmWanMbusC9 8 }

hmWanMbusC9Value01		OBJECT-TYPE
			SYNTAX	INTEGER
			MAX-ACCESS	read-only
			STATUS	current
			::= { hmWanMbusC9 9 }

hmWanMbusC9VIF02		OBJECT-TYPE
			SYNTAX	INTEGER
			MAX-ACCESS	read-only
			STATUS	current
			::= { hmWanMbusC9 10 }

hmWanMbusC9Value02		OBJECT-TYPE
			SYNTAX	INTEGER
			MAX-ACCESS	read-only
			STATUS	current
			::= { hmWanMbusC9 11 }

hmWanMbusC9VIF03		OBJECT-TYPE
			SYNTAX	INTEGER
			MAX-ACCESS	read-only
			STATUS	current
			::= { hmWanMbusC9 12 }

hmWanMbusC9Value03		OBJECT-TYPE
			SYNTAX	INTEGER
			MAX-ACCESS	read-only
			STATUS	current
			::= { hmWanMbusC9 13 }

hmWanMbusC9VIF04		OBJECT-TYPE
			SYNTAX	INTEGER
			MAX-ACCESS	read-only
			STATUS	current
			::= { hmWanMbusC9 14 }

hmWanMbusC9Value04		OBJECT-TYPE
			SYNTAX	INTEGER
			MAX-ACCESS	read-only
			STATUS	current
			::= { hmWanMbusC9 15 }

hmWanMbusC9VIF05		OBJECT-TYPE
			SYNTAX	INTEGER
			MAX-ACCESS	read-only
			STATUS	current
			::= { hmWanMbusC9 16 }

hmWanMbusC9Value05		OBJECT-TYPE
			SYNTAX	INTEGER
			MAX-ACCESS	read-only
			STATUS	current
			::= { hmWanMbusC9 17 }

hmWanMbusC9VIF06		OBJECT-TYPE
			SYNTAX	INTEGER
			MAX-ACCESS	read-only
			STATUS	current
			::= { hmWanMbusC9 18 }

hmWanMbusC9Value06		OBJECT-TYPE
			SYNTAX	INTEGER
			MAX-ACCESS	read-only
			STATUS	current
			::= { hmWanMbusC9 19 }

hmWanMbusC9VIF07		OBJECT-TYPE
			SYNTAX	INTEGER
			MAX-ACCESS	read-only
			STATUS	current
			::= { hmWanMbusC9 20 }

hmWanMbusC9Value07		OBJECT-TYPE
			SYNTAX	INTEGER
			MAX-ACCESS	read-only
			STATUS	current
			::= { hmWanMbusC9 21 }

hmWanMbusC9VIF08		OBJECT-TYPE
			SYNTAX	INTEGER
			MAX-ACCESS	read-only
			STATUS	current
			::= { hmWanMbusC9 22 }

hmWanMbusC9Value08		OBJECT-TYPE
			SYNTAX	INTEGER
			MAX-ACCESS	read-only
			STATUS	current
			::= { hmWanMbusC9 23 }

hmWanMbusC9VIF09		OBJECT-TYPE
			SYNTAX	INTEGER
			MAX-ACCESS	read-only
			STATUS	current
			::= { hmWanMbusC9 24 }

hmWanMbusC9Value09		OBJECT-TYPE
			SYNTAX	INTEGER
			MAX-ACCESS	read-only
			STATUS	current
			::= { hmWanMbusC9 25 }

hmWanMbusC9VIF0A		OBJECT-TYPE
			SYNTAX	INTEGER
			MAX-ACCESS	read-only
			STATUS	current
			::= { hmWanMbusC9 26 }

hmWanMbusC9Value0A		OBJECT-TYPE
			SYNTAX	INTEGER
			MAX-ACCESS	read-only
			STATUS	current
			::= { hmWanMbusC9 27 }

hmWanMbusC9VIF0B		OBJECT-TYPE
			SYNTAX	INTEGER
			MAX-ACCESS	read-only
			STATUS	current
			::= { hmWanMbusC9 28 }

hmWanMbusC9Value0B		OBJECT-TYPE
			SYNTAX	INTEGER
			MAX-ACCESS	read-only
			STATUS	current
			::= { hmWanMbusC9 29 }

hmWanMbusC9VIF0C		OBJECT-TYPE
			SYNTAX	INTEGER
			MAX-ACCESS	read-only
			STATUS	current
			::= { hmWanMbusC9 30 }

hmWanMbusC9Value0C		OBJECT-TYPE
			SYNTAX	INTEGER
			MAX-ACCESS	read-only
			STATUS	current
			::= { hmWanMbusC9 31 }

hmWanMbusC9VIF0D		OBJECT-TYPE
			SYNTAX	INTEGER
			MAX-ACCESS	read-only
			STATUS	current
			::= { hmWanMbusC9 32 }

hmWanMbusC9Value0D		OBJECT-TYPE
			SYNTAX	INTEGER
			MAX-ACCESS	read-only
			STATUS	current
			::= { hmWanMbusC9 33 }

hmWanMbusC9VIF0E		OBJECT-TYPE
			SYNTAX	INTEGER
			MAX-ACCESS	read-only
			STATUS	current
			::= { hmWanMbusC9 34 }

hmWanMbusC9Value0E		OBJECT-TYPE
			SYNTAX	INTEGER
			MAX-ACCESS	read-only
			STATUS	current
			::= { hmWanMbusC9 35 }

hmWanMbusC9VIF0F		OBJECT-TYPE
			SYNTAX	INTEGER
			MAX-ACCESS	read-only
			STATUS	current
			::= { hmWanMbusC9 36 }

hmWanMbusC9Value0F		OBJECT-TYPE
			SYNTAX	INTEGER
			MAX-ACCESS	read-only
			STATUS	current
			::= { hmWanMbusC9 37 }

hmWanMbusC9VIF10		OBJECT-TYPE
			SYNTAX	INTEGER
			MAX-ACCESS	read-only
			STATUS	current
			::= { hmWanMbusC9 38 }

hmWanMbusC9Value10		OBJECT-TYPE
			SYNTAX	INTEGER
			MAX-ACCESS	read-only
			STATUS	current
			::= { hmWanMbusC9 39 }

hmWanMbusC9VIF11		OBJECT-TYPE
			SYNTAX	INTEGER
			MAX-ACCESS	read-only
			STATUS	current
			::= { hmWanMbusC9 40 }

hmWanMbusC9Value11		OBJECT-TYPE
			SYNTAX	INTEGER
			MAX-ACCESS	read-only
			STATUS	current
			::= { hmWanMbusC9 41 }

hmWanMbusC9VIF12		OBJECT-TYPE
			SYNTAX	INTEGER
			MAX-ACCESS	read-only
			STATUS	current
			::= { hmWanMbusC9 42 }

hmWanMbusC9Value12		OBJECT-TYPE
			SYNTAX	INTEGER
			MAX-ACCESS	read-only
			STATUS	current
			::= { hmWanMbusC9 43 }

hmWanMbusC9VIF13		OBJECT-TYPE
			SYNTAX	INTEGER
			MAX-ACCESS	read-only
			STATUS	current
			::= { hmWanMbusC9 44 }

hmWanMbusC9Value13		OBJECT-TYPE
			SYNTAX	INTEGER
			MAX-ACCESS	read-only
			STATUS	current
			::= { hmWanMbusC9 45 }

hmWanMbusC9VIF14		OBJECT-TYPE
			SYNTAX	INTEGER
			MAX-ACCESS	read-only
			STATUS	current
			::= { hmWanMbusC9 46 }

hmWanMbusC9Value14		OBJECT-TYPE
			SYNTAX	INTEGER
			MAX-ACCESS	read-only
			STATUS	current
			::= { hmWanMbusC9 47 }

hmWanMbusC9VIF15		OBJECT-TYPE
			SYNTAX	INTEGER
			MAX-ACCESS	read-only
			STATUS	current
			::= { hmWanMbusC9 48 }

hmWanMbusC9Value15		OBJECT-TYPE
			SYNTAX	INTEGER
			MAX-ACCESS	read-only
			STATUS	current
			::= { hmWanMbusC9 49 }

hmWanMbusC9VIF16		OBJECT-TYPE
			SYNTAX	INTEGER
			MAX-ACCESS	read-only
			STATUS	current
			::= { hmWanMbusC9 50 }

hmWanMbusC9Value16		OBJECT-TYPE
			SYNTAX	INTEGER
			MAX-ACCESS	read-only
			STATUS	current
			::= { hmWanMbusC9 51 }

hmWanMbusC9VIF17		OBJECT-TYPE
			SYNTAX	INTEGER
			MAX-ACCESS	read-only
			STATUS	current
			::= { hmWanMbusC9 52 }

hmWanMbusC9Value17		OBJECT-TYPE
			SYNTAX	INTEGER
			MAX-ACCESS	read-only
			STATUS	current
			::= { hmWanMbusC9 53 }

hmWanMbusC9VIF18		OBJECT-TYPE
			SYNTAX	INTEGER
			MAX-ACCESS	read-only
			STATUS	current
			::= { hmWanMbusC9 54 }

hmWanMbusC9Value18		OBJECT-TYPE
			SYNTAX	INTEGER
			MAX-ACCESS	read-only
			STATUS	current
			::= { hmWanMbusC9 55 }

hmWanMbusC9VIF19		OBJECT-TYPE
			SYNTAX	INTEGER
			MAX-ACCESS	read-only
			STATUS	current
			::= { hmWanMbusC9 56 }

hmWanMbusC9Value19		OBJECT-TYPE
			SYNTAX	INTEGER
			MAX-ACCESS	read-only
			STATUS	current
			::= { hmWanMbusC9 57 }

hmWanMbusC9VIF1A		OBJECT-TYPE
			SYNTAX	INTEGER
			MAX-ACCESS	read-only
			STATUS	current
			::= { hmWanMbusC9 58 }

hmWanMbusC9Value1A		OBJECT-TYPE
			SYNTAX	INTEGER
			MAX-ACCESS	read-only
			STATUS	current
			::= { hmWanMbusC9 59 }

hmWanMbusC9VIF1B		OBJECT-TYPE
			SYNTAX	INTEGER
			MAX-ACCESS	read-only
			STATUS	current
			::= { hmWanMbusC9 60 }

hmWanMbusC9Value1B		OBJECT-TYPE
			SYNTAX	INTEGER
			MAX-ACCESS	read-only
			STATUS	current
			::= { hmWanMbusC9 61 }

hmWanMbusC9VIF1C		OBJECT-TYPE
			SYNTAX	INTEGER
			MAX-ACCESS	read-only
			STATUS	current
			::= { hmWanMbusC9 62 }

hmWanMbusC9Value1C		OBJECT-TYPE
			SYNTAX	INTEGER
			MAX-ACCESS	read-only
			STATUS	current
			::= { hmWanMbusC9 63 }

hmWanMbusC9VIF1D		OBJECT-TYPE
			SYNTAX	INTEGER
			MAX-ACCESS	read-only
			STATUS	current
			::= { hmWanMbusC9 64 }

hmWanMbusC9Value1D		OBJECT-TYPE
			SYNTAX	INTEGER
			MAX-ACCESS	read-only
			STATUS	current
			::= { hmWanMbusC9 65 }

hmWanMbusC9VIF1E		OBJECT-TYPE
			SYNTAX	INTEGER
			MAX-ACCESS	read-only
			STATUS	current
			::= { hmWanMbusC9 66 }

hmWanMbusC9Value1E		OBJECT-TYPE
			SYNTAX	INTEGER
			MAX-ACCESS	read-only
			STATUS	current
			::= { hmWanMbusC9 67 }

hmWanMbusC9VIF1F		OBJECT-TYPE
			SYNTAX	INTEGER
			MAX-ACCESS	read-only
			STATUS	current
			::= { hmWanMbusC9 68 }

hmWanMbusC9Value1F		OBJECT-TYPE
			SYNTAX	INTEGER
			MAX-ACCESS	read-only
			STATUS	current
			::= { hmWanMbusC9 69 }

hmWanMbusC9VIF20		OBJECT-TYPE
			SYNTAX	INTEGER
			MAX-ACCESS	read-only
			STATUS	current
			::= { hmWanMbusC9 70 }

hmWanMbusC9Value20		OBJECT-TYPE
			SYNTAX	INTEGER
			MAX-ACCESS	read-only
			STATUS	current
			::= { hmWanMbusC9 71 }

hmWanMbusC9VIF21		OBJECT-TYPE
			SYNTAX	INTEGER
			MAX-ACCESS	read-only
			STATUS	current
			::= { hmWanMbusC9 72 }

hmWanMbusC9Value21		OBJECT-TYPE
			SYNTAX	INTEGER
			MAX-ACCESS	read-only
			STATUS	current
			::= { hmWanMbusC9 73 }

hmWanMbusC9VIF22		OBJECT-TYPE
			SYNTAX	INTEGER
			MAX-ACCESS	read-only
			STATUS	current
			::= { hmWanMbusC9 74 }

hmWanMbusC9Value22		OBJECT-TYPE
			SYNTAX	INTEGER
			MAX-ACCESS	read-only
			STATUS	current
			::= { hmWanMbusC9 75 }

hmWanMbusC9VIF23		OBJECT-TYPE
			SYNTAX	INTEGER
			MAX-ACCESS	read-only
			STATUS	current
			::= { hmWanMbusC9 76 }

hmWanMbusC9Value23		OBJECT-TYPE
			SYNTAX	INTEGER
			MAX-ACCESS	read-only
			STATUS	current
			::= { hmWanMbusC9 77 }

hmWanMbusC9VIF24		OBJECT-TYPE
			SYNTAX	INTEGER
			MAX-ACCESS	read-only
			STATUS	current
			::= { hmWanMbusC9 78 }

hmWanMbusC9Value24		OBJECT-TYPE
			SYNTAX	INTEGER
			MAX-ACCESS	read-only
			STATUS	current
			::= { hmWanMbusC9 79 }

hmWanMbusC9VIF25		OBJECT-TYPE
			SYNTAX	INTEGER
			MAX-ACCESS	read-only
			STATUS	current
			::= { hmWanMbusC9 80 }

hmWanMbusC9Value25		OBJECT-TYPE
			SYNTAX	INTEGER
			MAX-ACCESS	read-only
			STATUS	current
			::= { hmWanMbusC9 81 }

hmWanMbusC9VIF26		OBJECT-TYPE
			SYNTAX	INTEGER
			MAX-ACCESS	read-only
			STATUS	current
			::= { hmWanMbusC9 82 }

hmWanMbusC9Value26		OBJECT-TYPE
			SYNTAX	INTEGER
			MAX-ACCESS	read-only
			STATUS	current
			::= { hmWanMbusC9 83 }

hmWanMbusC9VIF27		OBJECT-TYPE
			SYNTAX	INTEGER
			MAX-ACCESS	read-only
			STATUS	current
			::= { hmWanMbusC9 84 }

hmWanMbusC9Value27		OBJECT-TYPE
			SYNTAX	INTEGER
			MAX-ACCESS	read-only
			STATUS	current
			::= { hmWanMbusC9 85 }

hmWanMbusC9VIF28		OBJECT-TYPE
			SYNTAX	INTEGER
			MAX-ACCESS	read-only
			STATUS	current
			::= { hmWanMbusC9 86 }

hmWanMbusC9Value28		OBJECT-TYPE
			SYNTAX	INTEGER
			MAX-ACCESS	read-only
			STATUS	current
			::= { hmWanMbusC9 87 }

hmWanMbusC9VIF29		OBJECT-TYPE
			SYNTAX	INTEGER
			MAX-ACCESS	read-only
			STATUS	current
			::= { hmWanMbusC9 88 }

hmWanMbusC9Value29		OBJECT-TYPE
			SYNTAX	INTEGER
			MAX-ACCESS	read-only
			STATUS	current
			::= { hmWanMbusC9 89 }

hmWanMbusC9VIF2A		OBJECT-TYPE
			SYNTAX	INTEGER
			MAX-ACCESS	read-only
			STATUS	current
			::= { hmWanMbusC9 90 }

hmWanMbusC9Value2A		OBJECT-TYPE
			SYNTAX	INTEGER
			MAX-ACCESS	read-only
			STATUS	current
			::= { hmWanMbusC9 91 }

hmWanMbusC9VIF2B		OBJECT-TYPE
			SYNTAX	INTEGER
			MAX-ACCESS	read-only
			STATUS	current
			::= { hmWanMbusC9 92 }

hmWanMbusC9Value2B		OBJECT-TYPE
			SYNTAX	INTEGER
			MAX-ACCESS	read-only
			STATUS	current
			::= { hmWanMbusC9 93 }

hmWanMbusC9VIF2C		OBJECT-TYPE
			SYNTAX	INTEGER
			MAX-ACCESS	read-only
			STATUS	current
			::= { hmWanMbusC9 94 }

hmWanMbusC9Value2C		OBJECT-TYPE
			SYNTAX	INTEGER
			MAX-ACCESS	read-only
			STATUS	current
			::= { hmWanMbusC9 95 }

hmWanMbusC9VIF2D		OBJECT-TYPE
			SYNTAX	INTEGER
			MAX-ACCESS	read-only
			STATUS	current
			::= { hmWanMbusC9 96 }

hmWanMbusC9Value2D		OBJECT-TYPE
			SYNTAX	INTEGER
			MAX-ACCESS	read-only
			STATUS	current
			::= { hmWanMbusC9 97 }

hmWanMbusC9VIF2E		OBJECT-TYPE
			SYNTAX	INTEGER
			MAX-ACCESS	read-only
			STATUS	current
			::= { hmWanMbusC9 98 }

hmWanMbusC9Value2E		OBJECT-TYPE
			SYNTAX	INTEGER
			MAX-ACCESS	read-only
			STATUS	current
			::= { hmWanMbusC9 99 }

hmWanMbusC9VIF2F		OBJECT-TYPE
			SYNTAX	INTEGER
			MAX-ACCESS	read-only
			STATUS	current
			::= { hmWanMbusC9 100 }

hmWanMbusC9Value2F		OBJECT-TYPE
			SYNTAX	INTEGER
			MAX-ACCESS	read-only
			STATUS	current
			::= { hmWanMbusC9 101 }

hmWanMbusCA			OBJECT IDENTIFIER ::= { hmWanMbus 202 }

hmWanMbusCAIdNumber		OBJECT-TYPE
			SYNTAX	Gauge32
			MAX-ACCESS	read-only
			STATUS	current
			::= { hmWanMbusCA 1 }

hmWanMbusCAManufacturer	OBJECT-TYPE
			SYNTAX	Gauge32
			MAX-ACCESS	read-only
			STATUS	current
			::= { hmWanMbusCA 2 }

hmWanMbusCAVersion		OBJECT-TYPE
			SYNTAX	Gauge32
			MAX-ACCESS	read-only
			STATUS	current
			::= { hmWanMbusCA 3 }

hmWanMbusCAMedium		OBJECT-TYPE
			SYNTAX	Gauge32
			MAX-ACCESS	read-only
			STATUS	current
			::= { hmWanMbusCA 4 }

hmWanMbusCAStatus		OBJECT-TYPE
			SYNTAX	Gauge32
			MAX-ACCESS	read-only
			STATUS	current
			::= { hmWanMbusCA 5 }

hmWanMbusCAVIF00		OBJECT-TYPE
			SYNTAX	INTEGER
			MAX-ACCESS	read-only
			STATUS	current
			::= { hmWanMbusCA 6 }

hmWanMbusCAValue00		OBJECT-TYPE
			SYNTAX	INTEGER
			MAX-ACCESS	read-only
			STATUS	current
			::= { hmWanMbusCA 7 }

hmWanMbusCAVIF01		OBJECT-TYPE
			SYNTAX	INTEGER
			MAX-ACCESS	read-only
			STATUS	current
			::= { hmWanMbusCA 8 }

hmWanMbusCAValue01		OBJECT-TYPE
			SYNTAX	INTEGER
			MAX-ACCESS	read-only
			STATUS	current
			::= { hmWanMbusCA 9 }

hmWanMbusCAVIF02		OBJECT-TYPE
			SYNTAX	INTEGER
			MAX-ACCESS	read-only
			STATUS	current
			::= { hmWanMbusCA 10 }

hmWanMbusCAValue02		OBJECT-TYPE
			SYNTAX	INTEGER
			MAX-ACCESS	read-only
			STATUS	current
			::= { hmWanMbusCA 11 }

hmWanMbusCAVIF03		OBJECT-TYPE
			SYNTAX	INTEGER
			MAX-ACCESS	read-only
			STATUS	current
			::= { hmWanMbusCA 12 }

hmWanMbusCAValue03		OBJECT-TYPE
			SYNTAX	INTEGER
			MAX-ACCESS	read-only
			STATUS	current
			::= { hmWanMbusCA 13 }

hmWanMbusCAVIF04		OBJECT-TYPE
			SYNTAX	INTEGER
			MAX-ACCESS	read-only
			STATUS	current
			::= { hmWanMbusCA 14 }

hmWanMbusCAValue04		OBJECT-TYPE
			SYNTAX	INTEGER
			MAX-ACCESS	read-only
			STATUS	current
			::= { hmWanMbusCA 15 }

hmWanMbusCAVIF05		OBJECT-TYPE
			SYNTAX	INTEGER
			MAX-ACCESS	read-only
			STATUS	current
			::= { hmWanMbusCA 16 }

hmWanMbusCAValue05		OBJECT-TYPE
			SYNTAX	INTEGER
			MAX-ACCESS	read-only
			STATUS	current
			::= { hmWanMbusCA 17 }

hmWanMbusCAVIF06		OBJECT-TYPE
			SYNTAX	INTEGER
			MAX-ACCESS	read-only
			STATUS	current
			::= { hmWanMbusCA 18 }

hmWanMbusCAValue06		OBJECT-TYPE
			SYNTAX	INTEGER
			MAX-ACCESS	read-only
			STATUS	current
			::= { hmWanMbusCA 19 }

hmWanMbusCAVIF07		OBJECT-TYPE
			SYNTAX	INTEGER
			MAX-ACCESS	read-only
			STATUS	current
			::= { hmWanMbusCA 20 }

hmWanMbusCAValue07		OBJECT-TYPE
			SYNTAX	INTEGER
			MAX-ACCESS	read-only
			STATUS	current
			::= { hmWanMbusCA 21 }

hmWanMbusCAVIF08		OBJECT-TYPE
			SYNTAX	INTEGER
			MAX-ACCESS	read-only
			STATUS	current
			::= { hmWanMbusCA 22 }

hmWanMbusCAValue08		OBJECT-TYPE
			SYNTAX	INTEGER
			MAX-ACCESS	read-only
			STATUS	current
			::= { hmWanMbusCA 23 }

hmWanMbusCAVIF09		OBJECT-TYPE
			SYNTAX	INTEGER
			MAX-ACCESS	read-only
			STATUS	current
			::= { hmWanMbusCA 24 }

hmWanMbusCAValue09		OBJECT-TYPE
			SYNTAX	INTEGER
			MAX-ACCESS	read-only
			STATUS	current
			::= { hmWanMbusCA 25 }

hmWanMbusCAVIF0A		OBJECT-TYPE
			SYNTAX	INTEGER
			MAX-ACCESS	read-only
			STATUS	current
			::= { hmWanMbusCA 26 }

hmWanMbusCAValue0A		OBJECT-TYPE
			SYNTAX	INTEGER
			MAX-ACCESS	read-only
			STATUS	current
			::= { hmWanMbusCA 27 }

hmWanMbusCAVIF0B		OBJECT-TYPE
			SYNTAX	INTEGER
			MAX-ACCESS	read-only
			STATUS	current
			::= { hmWanMbusCA 28 }

hmWanMbusCAValue0B		OBJECT-TYPE
			SYNTAX	INTEGER
			MAX-ACCESS	read-only
			STATUS	current
			::= { hmWanMbusCA 29 }

hmWanMbusCAVIF0C		OBJECT-TYPE
			SYNTAX	INTEGER
			MAX-ACCESS	read-only
			STATUS	current
			::= { hmWanMbusCA 30 }

hmWanMbusCAValue0C		OBJECT-TYPE
			SYNTAX	INTEGER
			MAX-ACCESS	read-only
			STATUS	current
			::= { hmWanMbusCA 31 }

hmWanMbusCAVIF0D		OBJECT-TYPE
			SYNTAX	INTEGER
			MAX-ACCESS	read-only
			STATUS	current
			::= { hmWanMbusCA 32 }

hmWanMbusCAValue0D		OBJECT-TYPE
			SYNTAX	INTEGER
			MAX-ACCESS	read-only
			STATUS	current
			::= { hmWanMbusCA 33 }

hmWanMbusCAVIF0E		OBJECT-TYPE
			SYNTAX	INTEGER
			MAX-ACCESS	read-only
			STATUS	current
			::= { hmWanMbusCA 34 }

hmWanMbusCAValue0E		OBJECT-TYPE
			SYNTAX	INTEGER
			MAX-ACCESS	read-only
			STATUS	current
			::= { hmWanMbusCA 35 }

hmWanMbusCAVIF0F		OBJECT-TYPE
			SYNTAX	INTEGER
			MAX-ACCESS	read-only
			STATUS	current
			::= { hmWanMbusCA 36 }

hmWanMbusCAValue0F		OBJECT-TYPE
			SYNTAX	INTEGER
			MAX-ACCESS	read-only
			STATUS	current
			::= { hmWanMbusCA 37 }

hmWanMbusCAVIF10		OBJECT-TYPE
			SYNTAX	INTEGER
			MAX-ACCESS	read-only
			STATUS	current
			::= { hmWanMbusCA 38 }

hmWanMbusCAValue10		OBJECT-TYPE
			SYNTAX	INTEGER
			MAX-ACCESS	read-only
			STATUS	current
			::= { hmWanMbusCA 39 }

hmWanMbusCAVIF11		OBJECT-TYPE
			SYNTAX	INTEGER
			MAX-ACCESS	read-only
			STATUS	current
			::= { hmWanMbusCA 40 }

hmWanMbusCAValue11		OBJECT-TYPE
			SYNTAX	INTEGER
			MAX-ACCESS	read-only
			STATUS	current
			::= { hmWanMbusCA 41 }

hmWanMbusCAVIF12		OBJECT-TYPE
			SYNTAX	INTEGER
			MAX-ACCESS	read-only
			STATUS	current
			::= { hmWanMbusCA 42 }

hmWanMbusCAValue12		OBJECT-TYPE
			SYNTAX	INTEGER
			MAX-ACCESS	read-only
			STATUS	current
			::= { hmWanMbusCA 43 }

hmWanMbusCAVIF13		OBJECT-TYPE
			SYNTAX	INTEGER
			MAX-ACCESS	read-only
			STATUS	current
			::= { hmWanMbusCA 44 }

hmWanMbusCAValue13		OBJECT-TYPE
			SYNTAX	INTEGER
			MAX-ACCESS	read-only
			STATUS	current
			::= { hmWanMbusCA 45 }

hmWanMbusCAVIF14		OBJECT-TYPE
			SYNTAX	INTEGER
			MAX-ACCESS	read-only
			STATUS	current
			::= { hmWanMbusCA 46 }

hmWanMbusCAValue14		OBJECT-TYPE
			SYNTAX	INTEGER
			MAX-ACCESS	read-only
			STATUS	current
			::= { hmWanMbusCA 47 }

hmWanMbusCAVIF15		OBJECT-TYPE
			SYNTAX	INTEGER
			MAX-ACCESS	read-only
			STATUS	current
			::= { hmWanMbusCA 48 }

hmWanMbusCAValue15		OBJECT-TYPE
			SYNTAX	INTEGER
			MAX-ACCESS	read-only
			STATUS	current
			::= { hmWanMbusCA 49 }

hmWanMbusCAVIF16		OBJECT-TYPE
			SYNTAX	INTEGER
			MAX-ACCESS	read-only
			STATUS	current
			::= { hmWanMbusCA 50 }

hmWanMbusCAValue16		OBJECT-TYPE
			SYNTAX	INTEGER
			MAX-ACCESS	read-only
			STATUS	current
			::= { hmWanMbusCA 51 }

hmWanMbusCAVIF17		OBJECT-TYPE
			SYNTAX	INTEGER
			MAX-ACCESS	read-only
			STATUS	current
			::= { hmWanMbusCA 52 }

hmWanMbusCAValue17		OBJECT-TYPE
			SYNTAX	INTEGER
			MAX-ACCESS	read-only
			STATUS	current
			::= { hmWanMbusCA 53 }

hmWanMbusCAVIF18		OBJECT-TYPE
			SYNTAX	INTEGER
			MAX-ACCESS	read-only
			STATUS	current
			::= { hmWanMbusCA 54 }

hmWanMbusCAValue18		OBJECT-TYPE
			SYNTAX	INTEGER
			MAX-ACCESS	read-only
			STATUS	current
			::= { hmWanMbusCA 55 }

hmWanMbusCAVIF19		OBJECT-TYPE
			SYNTAX	INTEGER
			MAX-ACCESS	read-only
			STATUS	current
			::= { hmWanMbusCA 56 }

hmWanMbusCAValue19		OBJECT-TYPE
			SYNTAX	INTEGER
			MAX-ACCESS	read-only
			STATUS	current
			::= { hmWanMbusCA 57 }

hmWanMbusCAVIF1A		OBJECT-TYPE
			SYNTAX	INTEGER
			MAX-ACCESS	read-only
			STATUS	current
			::= { hmWanMbusCA 58 }

hmWanMbusCAValue1A		OBJECT-TYPE
			SYNTAX	INTEGER
			MAX-ACCESS	read-only
			STATUS	current
			::= { hmWanMbusCA 59 }

hmWanMbusCAVIF1B		OBJECT-TYPE
			SYNTAX	INTEGER
			MAX-ACCESS	read-only
			STATUS	current
			::= { hmWanMbusCA 60 }

hmWanMbusCAValue1B		OBJECT-TYPE
			SYNTAX	INTEGER
			MAX-ACCESS	read-only
			STATUS	current
			::= { hmWanMbusCA 61 }

hmWanMbusCAVIF1C		OBJECT-TYPE
			SYNTAX	INTEGER
			MAX-ACCESS	read-only
			STATUS	current
			::= { hmWanMbusCA 62 }

hmWanMbusCAValue1C		OBJECT-TYPE
			SYNTAX	INTEGER
			MAX-ACCESS	read-only
			STATUS	current
			::= { hmWanMbusCA 63 }

hmWanMbusCAVIF1D		OBJECT-TYPE
			SYNTAX	INTEGER
			MAX-ACCESS	read-only
			STATUS	current
			::= { hmWanMbusCA 64 }

hmWanMbusCAValue1D		OBJECT-TYPE
			SYNTAX	INTEGER
			MAX-ACCESS	read-only
			STATUS	current
			::= { hmWanMbusCA 65 }

hmWanMbusCAVIF1E		OBJECT-TYPE
			SYNTAX	INTEGER
			MAX-ACCESS	read-only
			STATUS	current
			::= { hmWanMbusCA 66 }

hmWanMbusCAValue1E		OBJECT-TYPE
			SYNTAX	INTEGER
			MAX-ACCESS	read-only
			STATUS	current
			::= { hmWanMbusCA 67 }

hmWanMbusCAVIF1F		OBJECT-TYPE
			SYNTAX	INTEGER
			MAX-ACCESS	read-only
			STATUS	current
			::= { hmWanMbusCA 68 }

hmWanMbusCAValue1F		OBJECT-TYPE
			SYNTAX	INTEGER
			MAX-ACCESS	read-only
			STATUS	current
			::= { hmWanMbusCA 69 }

hmWanMbusCAVIF20		OBJECT-TYPE
			SYNTAX	INTEGER
			MAX-ACCESS	read-only
			STATUS	current
			::= { hmWanMbusCA 70 }

hmWanMbusCAValue20		OBJECT-TYPE
			SYNTAX	INTEGER
			MAX-ACCESS	read-only
			STATUS	current
			::= { hmWanMbusCA 71 }

hmWanMbusCAVIF21		OBJECT-TYPE
			SYNTAX	INTEGER
			MAX-ACCESS	read-only
			STATUS	current
			::= { hmWanMbusCA 72 }

hmWanMbusCAValue21		OBJECT-TYPE
			SYNTAX	INTEGER
			MAX-ACCESS	read-only
			STATUS	current
			::= { hmWanMbusCA 73 }

hmWanMbusCAVIF22		OBJECT-TYPE
			SYNTAX	INTEGER
			MAX-ACCESS	read-only
			STATUS	current
			::= { hmWanMbusCA 74 }

hmWanMbusCAValue22		OBJECT-TYPE
			SYNTAX	INTEGER
			MAX-ACCESS	read-only
			STATUS	current
			::= { hmWanMbusCA 75 }

hmWanMbusCAVIF23		OBJECT-TYPE
			SYNTAX	INTEGER
			MAX-ACCESS	read-only
			STATUS	current
			::= { hmWanMbusCA 76 }

hmWanMbusCAValue23		OBJECT-TYPE
			SYNTAX	INTEGER
			MAX-ACCESS	read-only
			STATUS	current
			::= { hmWanMbusCA 77 }

hmWanMbusCAVIF24		OBJECT-TYPE
			SYNTAX	INTEGER
			MAX-ACCESS	read-only
			STATUS	current
			::= { hmWanMbusCA 78 }

hmWanMbusCAValue24		OBJECT-TYPE
			SYNTAX	INTEGER
			MAX-ACCESS	read-only
			STATUS	current
			::= { hmWanMbusCA 79 }

hmWanMbusCAVIF25		OBJECT-TYPE
			SYNTAX	INTEGER
			MAX-ACCESS	read-only
			STATUS	current
			::= { hmWanMbusCA 80 }

hmWanMbusCAValue25		OBJECT-TYPE
			SYNTAX	INTEGER
			MAX-ACCESS	read-only
			STATUS	current
			::= { hmWanMbusCA 81 }

hmWanMbusCAVIF26		OBJECT-TYPE
			SYNTAX	INTEGER
			MAX-ACCESS	read-only
			STATUS	current
			::= { hmWanMbusCA 82 }

hmWanMbusCAValue26		OBJECT-TYPE
			SYNTAX	INTEGER
			MAX-ACCESS	read-only
			STATUS	current
			::= { hmWanMbusCA 83 }

hmWanMbusCAVIF27		OBJECT-TYPE
			SYNTAX	INTEGER
			MAX-ACCESS	read-only
			STATUS	current
			::= { hmWanMbusCA 84 }

hmWanMbusCAValue27		OBJECT-TYPE
			SYNTAX	INTEGER
			MAX-ACCESS	read-only
			STATUS	current
			::= { hmWanMbusCA 85 }

hmWanMbusCAVIF28		OBJECT-TYPE
			SYNTAX	INTEGER
			MAX-ACCESS	read-only
			STATUS	current
			::= { hmWanMbusCA 86 }

hmWanMbusCAValue28		OBJECT-TYPE
			SYNTAX	INTEGER
			MAX-ACCESS	read-only
			STATUS	current
			::= { hmWanMbusCA 87 }

hmWanMbusCAVIF29		OBJECT-TYPE
			SYNTAX	INTEGER
			MAX-ACCESS	read-only
			STATUS	current
			::= { hmWanMbusCA 88 }

hmWanMbusCAValue29		OBJECT-TYPE
			SYNTAX	INTEGER
			MAX-ACCESS	read-only
			STATUS	current
			::= { hmWanMbusCA 89 }

hmWanMbusCAVIF2A		OBJECT-TYPE
			SYNTAX	INTEGER
			MAX-ACCESS	read-only
			STATUS	current
			::= { hmWanMbusCA 90 }

hmWanMbusCAValue2A		OBJECT-TYPE
			SYNTAX	INTEGER
			MAX-ACCESS	read-only
			STATUS	current
			::= { hmWanMbusCA 91 }

hmWanMbusCAVIF2B		OBJECT-TYPE
			SYNTAX	INTEGER
			MAX-ACCESS	read-only
			STATUS	current
			::= { hmWanMbusCA 92 }

hmWanMbusCAValue2B		OBJECT-TYPE
			SYNTAX	INTEGER
			MAX-ACCESS	read-only
			STATUS	current
			::= { hmWanMbusCA 93 }

hmWanMbusCAVIF2C		OBJECT-TYPE
			SYNTAX	INTEGER
			MAX-ACCESS	read-only
			STATUS	current
			::= { hmWanMbusCA 94 }

hmWanMbusCAValue2C		OBJECT-TYPE
			SYNTAX	INTEGER
			MAX-ACCESS	read-only
			STATUS	current
			::= { hmWanMbusCA 95 }

hmWanMbusCAVIF2D		OBJECT-TYPE
			SYNTAX	INTEGER
			MAX-ACCESS	read-only
			STATUS	current
			::= { hmWanMbusCA 96 }

hmWanMbusCAValue2D		OBJECT-TYPE
			SYNTAX	INTEGER
			MAX-ACCESS	read-only
			STATUS	current
			::= { hmWanMbusCA 97 }

hmWanMbusCAVIF2E		OBJECT-TYPE
			SYNTAX	INTEGER
			MAX-ACCESS	read-only
			STATUS	current
			::= { hmWanMbusCA 98 }

hmWanMbusCAValue2E		OBJECT-TYPE
			SYNTAX	INTEGER
			MAX-ACCESS	read-only
			STATUS	current
			::= { hmWanMbusCA 99 }

hmWanMbusCAVIF2F		OBJECT-TYPE
			SYNTAX	INTEGER
			MAX-ACCESS	read-only
			STATUS	current
			::= { hmWanMbusCA 100 }

hmWanMbusCAValue2F		OBJECT-TYPE
			SYNTAX	INTEGER
			MAX-ACCESS	read-only
			STATUS	current
			::= { hmWanMbusCA 101 }

hmWanMbusCB			OBJECT IDENTIFIER ::= { hmWanMbus 203 }

hmWanMbusCBIdNumber		OBJECT-TYPE
			SYNTAX	Gauge32
			MAX-ACCESS	read-only
			STATUS	current
			::= { hmWanMbusCB 1 }

hmWanMbusCBManufacturer	OBJECT-TYPE
			SYNTAX	Gauge32
			MAX-ACCESS	read-only
			STATUS	current
			::= { hmWanMbusCB 2 }

hmWanMbusCBVersion		OBJECT-TYPE
			SYNTAX	Gauge32
			MAX-ACCESS	read-only
			STATUS	current
			::= { hmWanMbusCB 3 }

hmWanMbusCBMedium		OBJECT-TYPE
			SYNTAX	Gauge32
			MAX-ACCESS	read-only
			STATUS	current
			::= { hmWanMbusCB 4 }

hmWanMbusCBStatus		OBJECT-TYPE
			SYNTAX	Gauge32
			MAX-ACCESS	read-only
			STATUS	current
			::= { hmWanMbusCB 5 }

hmWanMbusCBVIF00		OBJECT-TYPE
			SYNTAX	INTEGER
			MAX-ACCESS	read-only
			STATUS	current
			::= { hmWanMbusCB 6 }

hmWanMbusCBValue00		OBJECT-TYPE
			SYNTAX	INTEGER
			MAX-ACCESS	read-only
			STATUS	current
			::= { hmWanMbusCB 7 }

hmWanMbusCBVIF01		OBJECT-TYPE
			SYNTAX	INTEGER
			MAX-ACCESS	read-only
			STATUS	current
			::= { hmWanMbusCB 8 }

hmWanMbusCBValue01		OBJECT-TYPE
			SYNTAX	INTEGER
			MAX-ACCESS	read-only
			STATUS	current
			::= { hmWanMbusCB 9 }

hmWanMbusCBVIF02		OBJECT-TYPE
			SYNTAX	INTEGER
			MAX-ACCESS	read-only
			STATUS	current
			::= { hmWanMbusCB 10 }

hmWanMbusCBValue02		OBJECT-TYPE
			SYNTAX	INTEGER
			MAX-ACCESS	read-only
			STATUS	current
			::= { hmWanMbusCB 11 }

hmWanMbusCBVIF03		OBJECT-TYPE
			SYNTAX	INTEGER
			MAX-ACCESS	read-only
			STATUS	current
			::= { hmWanMbusCB 12 }

hmWanMbusCBValue03		OBJECT-TYPE
			SYNTAX	INTEGER
			MAX-ACCESS	read-only
			STATUS	current
			::= { hmWanMbusCB 13 }

hmWanMbusCBVIF04		OBJECT-TYPE
			SYNTAX	INTEGER
			MAX-ACCESS	read-only
			STATUS	current
			::= { hmWanMbusCB 14 }

hmWanMbusCBValue04		OBJECT-TYPE
			SYNTAX	INTEGER
			MAX-ACCESS	read-only
			STATUS	current
			::= { hmWanMbusCB 15 }

hmWanMbusCBVIF05		OBJECT-TYPE
			SYNTAX	INTEGER
			MAX-ACCESS	read-only
			STATUS	current
			::= { hmWanMbusCB 16 }

hmWanMbusCBValue05		OBJECT-TYPE
			SYNTAX	INTEGER
			MAX-ACCESS	read-only
			STATUS	current
			::= { hmWanMbusCB 17 }

hmWanMbusCBVIF06		OBJECT-TYPE
			SYNTAX	INTEGER
			MAX-ACCESS	read-only
			STATUS	current
			::= { hmWanMbusCB 18 }

hmWanMbusCBValue06		OBJECT-TYPE
			SYNTAX	INTEGER
			MAX-ACCESS	read-only
			STATUS	current
			::= { hmWanMbusCB 19 }

hmWanMbusCBVIF07		OBJECT-TYPE
			SYNTAX	INTEGER
			MAX-ACCESS	read-only
			STATUS	current
			::= { hmWanMbusCB 20 }

hmWanMbusCBValue07		OBJECT-TYPE
			SYNTAX	INTEGER
			MAX-ACCESS	read-only
			STATUS	current
			::= { hmWanMbusCB 21 }

hmWanMbusCBVIF08		OBJECT-TYPE
			SYNTAX	INTEGER
			MAX-ACCESS	read-only
			STATUS	current
			::= { hmWanMbusCB 22 }

hmWanMbusCBValue08		OBJECT-TYPE
			SYNTAX	INTEGER
			MAX-ACCESS	read-only
			STATUS	current
			::= { hmWanMbusCB 23 }

hmWanMbusCBVIF09		OBJECT-TYPE
			SYNTAX	INTEGER
			MAX-ACCESS	read-only
			STATUS	current
			::= { hmWanMbusCB 24 }

hmWanMbusCBValue09		OBJECT-TYPE
			SYNTAX	INTEGER
			MAX-ACCESS	read-only
			STATUS	current
			::= { hmWanMbusCB 25 }

hmWanMbusCBVIF0A		OBJECT-TYPE
			SYNTAX	INTEGER
			MAX-ACCESS	read-only
			STATUS	current
			::= { hmWanMbusCB 26 }

hmWanMbusCBValue0A		OBJECT-TYPE
			SYNTAX	INTEGER
			MAX-ACCESS	read-only
			STATUS	current
			::= { hmWanMbusCB 27 }

hmWanMbusCBVIF0B		OBJECT-TYPE
			SYNTAX	INTEGER
			MAX-ACCESS	read-only
			STATUS	current
			::= { hmWanMbusCB 28 }

hmWanMbusCBValue0B		OBJECT-TYPE
			SYNTAX	INTEGER
			MAX-ACCESS	read-only
			STATUS	current
			::= { hmWanMbusCB 29 }

hmWanMbusCBVIF0C		OBJECT-TYPE
			SYNTAX	INTEGER
			MAX-ACCESS	read-only
			STATUS	current
			::= { hmWanMbusCB 30 }

hmWanMbusCBValue0C		OBJECT-TYPE
			SYNTAX	INTEGER
			MAX-ACCESS	read-only
			STATUS	current
			::= { hmWanMbusCB 31 }

hmWanMbusCBVIF0D		OBJECT-TYPE
			SYNTAX	INTEGER
			MAX-ACCESS	read-only
			STATUS	current
			::= { hmWanMbusCB 32 }

hmWanMbusCBValue0D		OBJECT-TYPE
			SYNTAX	INTEGER
			MAX-ACCESS	read-only
			STATUS	current
			::= { hmWanMbusCB 33 }

hmWanMbusCBVIF0E		OBJECT-TYPE
			SYNTAX	INTEGER
			MAX-ACCESS	read-only
			STATUS	current
			::= { hmWanMbusCB 34 }

hmWanMbusCBValue0E		OBJECT-TYPE
			SYNTAX	INTEGER
			MAX-ACCESS	read-only
			STATUS	current
			::= { hmWanMbusCB 35 }

hmWanMbusCBVIF0F		OBJECT-TYPE
			SYNTAX	INTEGER
			MAX-ACCESS	read-only
			STATUS	current
			::= { hmWanMbusCB 36 }

hmWanMbusCBValue0F		OBJECT-TYPE
			SYNTAX	INTEGER
			MAX-ACCESS	read-only
			STATUS	current
			::= { hmWanMbusCB 37 }

hmWanMbusCBVIF10		OBJECT-TYPE
			SYNTAX	INTEGER
			MAX-ACCESS	read-only
			STATUS	current
			::= { hmWanMbusCB 38 }

hmWanMbusCBValue10		OBJECT-TYPE
			SYNTAX	INTEGER
			MAX-ACCESS	read-only
			STATUS	current
			::= { hmWanMbusCB 39 }

hmWanMbusCBVIF11		OBJECT-TYPE
			SYNTAX	INTEGER
			MAX-ACCESS	read-only
			STATUS	current
			::= { hmWanMbusCB 40 }

hmWanMbusCBValue11		OBJECT-TYPE
			SYNTAX	INTEGER
			MAX-ACCESS	read-only
			STATUS	current
			::= { hmWanMbusCB 41 }

hmWanMbusCBVIF12		OBJECT-TYPE
			SYNTAX	INTEGER
			MAX-ACCESS	read-only
			STATUS	current
			::= { hmWanMbusCB 42 }

hmWanMbusCBValue12		OBJECT-TYPE
			SYNTAX	INTEGER
			MAX-ACCESS	read-only
			STATUS	current
			::= { hmWanMbusCB 43 }

hmWanMbusCBVIF13		OBJECT-TYPE
			SYNTAX	INTEGER
			MAX-ACCESS	read-only
			STATUS	current
			::= { hmWanMbusCB 44 }

hmWanMbusCBValue13		OBJECT-TYPE
			SYNTAX	INTEGER
			MAX-ACCESS	read-only
			STATUS	current
			::= { hmWanMbusCB 45 }

hmWanMbusCBVIF14		OBJECT-TYPE
			SYNTAX	INTEGER
			MAX-ACCESS	read-only
			STATUS	current
			::= { hmWanMbusCB 46 }

hmWanMbusCBValue14		OBJECT-TYPE
			SYNTAX	INTEGER
			MAX-ACCESS	read-only
			STATUS	current
			::= { hmWanMbusCB 47 }

hmWanMbusCBVIF15		OBJECT-TYPE
			SYNTAX	INTEGER
			MAX-ACCESS	read-only
			STATUS	current
			::= { hmWanMbusCB 48 }

hmWanMbusCBValue15		OBJECT-TYPE
			SYNTAX	INTEGER
			MAX-ACCESS	read-only
			STATUS	current
			::= { hmWanMbusCB 49 }

hmWanMbusCBVIF16		OBJECT-TYPE
			SYNTAX	INTEGER
			MAX-ACCESS	read-only
			STATUS	current
			::= { hmWanMbusCB 50 }

hmWanMbusCBValue16		OBJECT-TYPE
			SYNTAX	INTEGER
			MAX-ACCESS	read-only
			STATUS	current
			::= { hmWanMbusCB 51 }

hmWanMbusCBVIF17		OBJECT-TYPE
			SYNTAX	INTEGER
			MAX-ACCESS	read-only
			STATUS	current
			::= { hmWanMbusCB 52 }

hmWanMbusCBValue17		OBJECT-TYPE
			SYNTAX	INTEGER
			MAX-ACCESS	read-only
			STATUS	current
			::= { hmWanMbusCB 53 }

hmWanMbusCBVIF18		OBJECT-TYPE
			SYNTAX	INTEGER
			MAX-ACCESS	read-only
			STATUS	current
			::= { hmWanMbusCB 54 }

hmWanMbusCBValue18		OBJECT-TYPE
			SYNTAX	INTEGER
			MAX-ACCESS	read-only
			STATUS	current
			::= { hmWanMbusCB 55 }

hmWanMbusCBVIF19		OBJECT-TYPE
			SYNTAX	INTEGER
			MAX-ACCESS	read-only
			STATUS	current
			::= { hmWanMbusCB 56 }

hmWanMbusCBValue19		OBJECT-TYPE
			SYNTAX	INTEGER
			MAX-ACCESS	read-only
			STATUS	current
			::= { hmWanMbusCB 57 }

hmWanMbusCBVIF1A		OBJECT-TYPE
			SYNTAX	INTEGER
			MAX-ACCESS	read-only
			STATUS	current
			::= { hmWanMbusCB 58 }

hmWanMbusCBValue1A		OBJECT-TYPE
			SYNTAX	INTEGER
			MAX-ACCESS	read-only
			STATUS	current
			::= { hmWanMbusCB 59 }

hmWanMbusCBVIF1B		OBJECT-TYPE
			SYNTAX	INTEGER
			MAX-ACCESS	read-only
			STATUS	current
			::= { hmWanMbusCB 60 }

hmWanMbusCBValue1B		OBJECT-TYPE
			SYNTAX	INTEGER
			MAX-ACCESS	read-only
			STATUS	current
			::= { hmWanMbusCB 61 }

hmWanMbusCBVIF1C		OBJECT-TYPE
			SYNTAX	INTEGER
			MAX-ACCESS	read-only
			STATUS	current
			::= { hmWanMbusCB 62 }

hmWanMbusCBValue1C		OBJECT-TYPE
			SYNTAX	INTEGER
			MAX-ACCESS	read-only
			STATUS	current
			::= { hmWanMbusCB 63 }

hmWanMbusCBVIF1D		OBJECT-TYPE
			SYNTAX	INTEGER
			MAX-ACCESS	read-only
			STATUS	current
			::= { hmWanMbusCB 64 }

hmWanMbusCBValue1D		OBJECT-TYPE
			SYNTAX	INTEGER
			MAX-ACCESS	read-only
			STATUS	current
			::= { hmWanMbusCB 65 }

hmWanMbusCBVIF1E		OBJECT-TYPE
			SYNTAX	INTEGER
			MAX-ACCESS	read-only
			STATUS	current
			::= { hmWanMbusCB 66 }

hmWanMbusCBValue1E		OBJECT-TYPE
			SYNTAX	INTEGER
			MAX-ACCESS	read-only
			STATUS	current
			::= { hmWanMbusCB 67 }

hmWanMbusCBVIF1F		OBJECT-TYPE
			SYNTAX	INTEGER
			MAX-ACCESS	read-only
			STATUS	current
			::= { hmWanMbusCB 68 }

hmWanMbusCBValue1F		OBJECT-TYPE
			SYNTAX	INTEGER
			MAX-ACCESS	read-only
			STATUS	current
			::= { hmWanMbusCB 69 }

hmWanMbusCBVIF20		OBJECT-TYPE
			SYNTAX	INTEGER
			MAX-ACCESS	read-only
			STATUS	current
			::= { hmWanMbusCB 70 }

hmWanMbusCBValue20		OBJECT-TYPE
			SYNTAX	INTEGER
			MAX-ACCESS	read-only
			STATUS	current
			::= { hmWanMbusCB 71 }

hmWanMbusCBVIF21		OBJECT-TYPE
			SYNTAX	INTEGER
			MAX-ACCESS	read-only
			STATUS	current
			::= { hmWanMbusCB 72 }

hmWanMbusCBValue21		OBJECT-TYPE
			SYNTAX	INTEGER
			MAX-ACCESS	read-only
			STATUS	current
			::= { hmWanMbusCB 73 }

hmWanMbusCBVIF22		OBJECT-TYPE
			SYNTAX	INTEGER
			MAX-ACCESS	read-only
			STATUS	current
			::= { hmWanMbusCB 74 }

hmWanMbusCBValue22		OBJECT-TYPE
			SYNTAX	INTEGER
			MAX-ACCESS	read-only
			STATUS	current
			::= { hmWanMbusCB 75 }

hmWanMbusCBVIF23		OBJECT-TYPE
			SYNTAX	INTEGER
			MAX-ACCESS	read-only
			STATUS	current
			::= { hmWanMbusCB 76 }

hmWanMbusCBValue23		OBJECT-TYPE
			SYNTAX	INTEGER
			MAX-ACCESS	read-only
			STATUS	current
			::= { hmWanMbusCB 77 }

hmWanMbusCBVIF24		OBJECT-TYPE
			SYNTAX	INTEGER
			MAX-ACCESS	read-only
			STATUS	current
			::= { hmWanMbusCB 78 }

hmWanMbusCBValue24		OBJECT-TYPE
			SYNTAX	INTEGER
			MAX-ACCESS	read-only
			STATUS	current
			::= { hmWanMbusCB 79 }

hmWanMbusCBVIF25		OBJECT-TYPE
			SYNTAX	INTEGER
			MAX-ACCESS	read-only
			STATUS	current
			::= { hmWanMbusCB 80 }

hmWanMbusCBValue25		OBJECT-TYPE
			SYNTAX	INTEGER
			MAX-ACCESS	read-only
			STATUS	current
			::= { hmWanMbusCB 81 }

hmWanMbusCBVIF26		OBJECT-TYPE
			SYNTAX	INTEGER
			MAX-ACCESS	read-only
			STATUS	current
			::= { hmWanMbusCB 82 }

hmWanMbusCBValue26		OBJECT-TYPE
			SYNTAX	INTEGER
			MAX-ACCESS	read-only
			STATUS	current
			::= { hmWanMbusCB 83 }

hmWanMbusCBVIF27		OBJECT-TYPE
			SYNTAX	INTEGER
			MAX-ACCESS	read-only
			STATUS	current
			::= { hmWanMbusCB 84 }

hmWanMbusCBValue27		OBJECT-TYPE
			SYNTAX	INTEGER
			MAX-ACCESS	read-only
			STATUS	current
			::= { hmWanMbusCB 85 }

hmWanMbusCBVIF28		OBJECT-TYPE
			SYNTAX	INTEGER
			MAX-ACCESS	read-only
			STATUS	current
			::= { hmWanMbusCB 86 }

hmWanMbusCBValue28		OBJECT-TYPE
			SYNTAX	INTEGER
			MAX-ACCESS	read-only
			STATUS	current
			::= { hmWanMbusCB 87 }

hmWanMbusCBVIF29		OBJECT-TYPE
			SYNTAX	INTEGER
			MAX-ACCESS	read-only
			STATUS	current
			::= { hmWanMbusCB 88 }

hmWanMbusCBValue29		OBJECT-TYPE
			SYNTAX	INTEGER
			MAX-ACCESS	read-only
			STATUS	current
			::= { hmWanMbusCB 89 }

hmWanMbusCBVIF2A		OBJECT-TYPE
			SYNTAX	INTEGER
			MAX-ACCESS	read-only
			STATUS	current
			::= { hmWanMbusCB 90 }

hmWanMbusCBValue2A		OBJECT-TYPE
			SYNTAX	INTEGER
			MAX-ACCESS	read-only
			STATUS	current
			::= { hmWanMbusCB 91 }

hmWanMbusCBVIF2B		OBJECT-TYPE
			SYNTAX	INTEGER
			MAX-ACCESS	read-only
			STATUS	current
			::= { hmWanMbusCB 92 }

hmWanMbusCBValue2B		OBJECT-TYPE
			SYNTAX	INTEGER
			MAX-ACCESS	read-only
			STATUS	current
			::= { hmWanMbusCB 93 }

hmWanMbusCBVIF2C		OBJECT-TYPE
			SYNTAX	INTEGER
			MAX-ACCESS	read-only
			STATUS	current
			::= { hmWanMbusCB 94 }

hmWanMbusCBValue2C		OBJECT-TYPE
			SYNTAX	INTEGER
			MAX-ACCESS	read-only
			STATUS	current
			::= { hmWanMbusCB 95 }

hmWanMbusCBVIF2D		OBJECT-TYPE
			SYNTAX	INTEGER
			MAX-ACCESS	read-only
			STATUS	current
			::= { hmWanMbusCB 96 }

hmWanMbusCBValue2D		OBJECT-TYPE
			SYNTAX	INTEGER
			MAX-ACCESS	read-only
			STATUS	current
			::= { hmWanMbusCB 97 }

hmWanMbusCBVIF2E		OBJECT-TYPE
			SYNTAX	INTEGER
			MAX-ACCESS	read-only
			STATUS	current
			::= { hmWanMbusCB 98 }

hmWanMbusCBValue2E		OBJECT-TYPE
			SYNTAX	INTEGER
			MAX-ACCESS	read-only
			STATUS	current
			::= { hmWanMbusCB 99 }

hmWanMbusCBVIF2F		OBJECT-TYPE
			SYNTAX	INTEGER
			MAX-ACCESS	read-only
			STATUS	current
			::= { hmWanMbusCB 100 }

hmWanMbusCBValue2F		OBJECT-TYPE
			SYNTAX	INTEGER
			MAX-ACCESS	read-only
			STATUS	current
			::= { hmWanMbusCB 101 }

hmWanMbusCC			OBJECT IDENTIFIER ::= { hmWanMbus 204 }

hmWanMbusCCIdNumber		OBJECT-TYPE
			SYNTAX	Gauge32
			MAX-ACCESS	read-only
			STATUS	current
			::= { hmWanMbusCC 1 }

hmWanMbusCCManufacturer	OBJECT-TYPE
			SYNTAX	Gauge32
			MAX-ACCESS	read-only
			STATUS	current
			::= { hmWanMbusCC 2 }

hmWanMbusCCVersion		OBJECT-TYPE
			SYNTAX	Gauge32
			MAX-ACCESS	read-only
			STATUS	current
			::= { hmWanMbusCC 3 }

hmWanMbusCCMedium		OBJECT-TYPE
			SYNTAX	Gauge32
			MAX-ACCESS	read-only
			STATUS	current
			::= { hmWanMbusCC 4 }

hmWanMbusCCStatus		OBJECT-TYPE
			SYNTAX	Gauge32
			MAX-ACCESS	read-only
			STATUS	current
			::= { hmWanMbusCC 5 }

hmWanMbusCCVIF00		OBJECT-TYPE
			SYNTAX	INTEGER
			MAX-ACCESS	read-only
			STATUS	current
			::= { hmWanMbusCC 6 }

hmWanMbusCCValue00		OBJECT-TYPE
			SYNTAX	INTEGER
			MAX-ACCESS	read-only
			STATUS	current
			::= { hmWanMbusCC 7 }

hmWanMbusCCVIF01		OBJECT-TYPE
			SYNTAX	INTEGER
			MAX-ACCESS	read-only
			STATUS	current
			::= { hmWanMbusCC 8 }

hmWanMbusCCValue01		OBJECT-TYPE
			SYNTAX	INTEGER
			MAX-ACCESS	read-only
			STATUS	current
			::= { hmWanMbusCC 9 }

hmWanMbusCCVIF02		OBJECT-TYPE
			SYNTAX	INTEGER
			MAX-ACCESS	read-only
			STATUS	current
			::= { hmWanMbusCC 10 }

hmWanMbusCCValue02		OBJECT-TYPE
			SYNTAX	INTEGER
			MAX-ACCESS	read-only
			STATUS	current
			::= { hmWanMbusCC 11 }

hmWanMbusCCVIF03		OBJECT-TYPE
			SYNTAX	INTEGER
			MAX-ACCESS	read-only
			STATUS	current
			::= { hmWanMbusCC 12 }

hmWanMbusCCValue03		OBJECT-TYPE
			SYNTAX	INTEGER
			MAX-ACCESS	read-only
			STATUS	current
			::= { hmWanMbusCC 13 }

hmWanMbusCCVIF04		OBJECT-TYPE
			SYNTAX	INTEGER
			MAX-ACCESS	read-only
			STATUS	current
			::= { hmWanMbusCC 14 }

hmWanMbusCCValue04		OBJECT-TYPE
			SYNTAX	INTEGER
			MAX-ACCESS	read-only
			STATUS	current
			::= { hmWanMbusCC 15 }

hmWanMbusCCVIF05		OBJECT-TYPE
			SYNTAX	INTEGER
			MAX-ACCESS	read-only
			STATUS	current
			::= { hmWanMbusCC 16 }

hmWanMbusCCValue05		OBJECT-TYPE
			SYNTAX	INTEGER
			MAX-ACCESS	read-only
			STATUS	current
			::= { hmWanMbusCC 17 }

hmWanMbusCCVIF06		OBJECT-TYPE
			SYNTAX	INTEGER
			MAX-ACCESS	read-only
			STATUS	current
			::= { hmWanMbusCC 18 }

hmWanMbusCCValue06		OBJECT-TYPE
			SYNTAX	INTEGER
			MAX-ACCESS	read-only
			STATUS	current
			::= { hmWanMbusCC 19 }

hmWanMbusCCVIF07		OBJECT-TYPE
			SYNTAX	INTEGER
			MAX-ACCESS	read-only
			STATUS	current
			::= { hmWanMbusCC 20 }

hmWanMbusCCValue07		OBJECT-TYPE
			SYNTAX	INTEGER
			MAX-ACCESS	read-only
			STATUS	current
			::= { hmWanMbusCC 21 }

hmWanMbusCCVIF08		OBJECT-TYPE
			SYNTAX	INTEGER
			MAX-ACCESS	read-only
			STATUS	current
			::= { hmWanMbusCC 22 }

hmWanMbusCCValue08		OBJECT-TYPE
			SYNTAX	INTEGER
			MAX-ACCESS	read-only
			STATUS	current
			::= { hmWanMbusCC 23 }

hmWanMbusCCVIF09		OBJECT-TYPE
			SYNTAX	INTEGER
			MAX-ACCESS	read-only
			STATUS	current
			::= { hmWanMbusCC 24 }

hmWanMbusCCValue09		OBJECT-TYPE
			SYNTAX	INTEGER
			MAX-ACCESS	read-only
			STATUS	current
			::= { hmWanMbusCC 25 }

hmWanMbusCCVIF0A		OBJECT-TYPE
			SYNTAX	INTEGER
			MAX-ACCESS	read-only
			STATUS	current
			::= { hmWanMbusCC 26 }

hmWanMbusCCValue0A		OBJECT-TYPE
			SYNTAX	INTEGER
			MAX-ACCESS	read-only
			STATUS	current
			::= { hmWanMbusCC 27 }

hmWanMbusCCVIF0B		OBJECT-TYPE
			SYNTAX	INTEGER
			MAX-ACCESS	read-only
			STATUS	current
			::= { hmWanMbusCC 28 }

hmWanMbusCCValue0B		OBJECT-TYPE
			SYNTAX	INTEGER
			MAX-ACCESS	read-only
			STATUS	current
			::= { hmWanMbusCC 29 }

hmWanMbusCCVIF0C		OBJECT-TYPE
			SYNTAX	INTEGER
			MAX-ACCESS	read-only
			STATUS	current
			::= { hmWanMbusCC 30 }

hmWanMbusCCValue0C		OBJECT-TYPE
			SYNTAX	INTEGER
			MAX-ACCESS	read-only
			STATUS	current
			::= { hmWanMbusCC 31 }

hmWanMbusCCVIF0D		OBJECT-TYPE
			SYNTAX	INTEGER
			MAX-ACCESS	read-only
			STATUS	current
			::= { hmWanMbusCC 32 }

hmWanMbusCCValue0D		OBJECT-TYPE
			SYNTAX	INTEGER
			MAX-ACCESS	read-only
			STATUS	current
			::= { hmWanMbusCC 33 }

hmWanMbusCCVIF0E		OBJECT-TYPE
			SYNTAX	INTEGER
			MAX-ACCESS	read-only
			STATUS	current
			::= { hmWanMbusCC 34 }

hmWanMbusCCValue0E		OBJECT-TYPE
			SYNTAX	INTEGER
			MAX-ACCESS	read-only
			STATUS	current
			::= { hmWanMbusCC 35 }

hmWanMbusCCVIF0F		OBJECT-TYPE
			SYNTAX	INTEGER
			MAX-ACCESS	read-only
			STATUS	current
			::= { hmWanMbusCC 36 }

hmWanMbusCCValue0F		OBJECT-TYPE
			SYNTAX	INTEGER
			MAX-ACCESS	read-only
			STATUS	current
			::= { hmWanMbusCC 37 }

hmWanMbusCCVIF10		OBJECT-TYPE
			SYNTAX	INTEGER
			MAX-ACCESS	read-only
			STATUS	current
			::= { hmWanMbusCC 38 }

hmWanMbusCCValue10		OBJECT-TYPE
			SYNTAX	INTEGER
			MAX-ACCESS	read-only
			STATUS	current
			::= { hmWanMbusCC 39 }

hmWanMbusCCVIF11		OBJECT-TYPE
			SYNTAX	INTEGER
			MAX-ACCESS	read-only
			STATUS	current
			::= { hmWanMbusCC 40 }

hmWanMbusCCValue11		OBJECT-TYPE
			SYNTAX	INTEGER
			MAX-ACCESS	read-only
			STATUS	current
			::= { hmWanMbusCC 41 }

hmWanMbusCCVIF12		OBJECT-TYPE
			SYNTAX	INTEGER
			MAX-ACCESS	read-only
			STATUS	current
			::= { hmWanMbusCC 42 }

hmWanMbusCCValue12		OBJECT-TYPE
			SYNTAX	INTEGER
			MAX-ACCESS	read-only
			STATUS	current
			::= { hmWanMbusCC 43 }

hmWanMbusCCVIF13		OBJECT-TYPE
			SYNTAX	INTEGER
			MAX-ACCESS	read-only
			STATUS	current
			::= { hmWanMbusCC 44 }

hmWanMbusCCValue13		OBJECT-TYPE
			SYNTAX	INTEGER
			MAX-ACCESS	read-only
			STATUS	current
			::= { hmWanMbusCC 45 }

hmWanMbusCCVIF14		OBJECT-TYPE
			SYNTAX	INTEGER
			MAX-ACCESS	read-only
			STATUS	current
			::= { hmWanMbusCC 46 }

hmWanMbusCCValue14		OBJECT-TYPE
			SYNTAX	INTEGER
			MAX-ACCESS	read-only
			STATUS	current
			::= { hmWanMbusCC 47 }

hmWanMbusCCVIF15		OBJECT-TYPE
			SYNTAX	INTEGER
			MAX-ACCESS	read-only
			STATUS	current
			::= { hmWanMbusCC 48 }

hmWanMbusCCValue15		OBJECT-TYPE
			SYNTAX	INTEGER
			MAX-ACCESS	read-only
			STATUS	current
			::= { hmWanMbusCC 49 }

hmWanMbusCCVIF16		OBJECT-TYPE
			SYNTAX	INTEGER
			MAX-ACCESS	read-only
			STATUS	current
			::= { hmWanMbusCC 50 }

hmWanMbusCCValue16		OBJECT-TYPE
			SYNTAX	INTEGER
			MAX-ACCESS	read-only
			STATUS	current
			::= { hmWanMbusCC 51 }

hmWanMbusCCVIF17		OBJECT-TYPE
			SYNTAX	INTEGER
			MAX-ACCESS	read-only
			STATUS	current
			::= { hmWanMbusCC 52 }

hmWanMbusCCValue17		OBJECT-TYPE
			SYNTAX	INTEGER
			MAX-ACCESS	read-only
			STATUS	current
			::= { hmWanMbusCC 53 }

hmWanMbusCCVIF18		OBJECT-TYPE
			SYNTAX	INTEGER
			MAX-ACCESS	read-only
			STATUS	current
			::= { hmWanMbusCC 54 }

hmWanMbusCCValue18		OBJECT-TYPE
			SYNTAX	INTEGER
			MAX-ACCESS	read-only
			STATUS	current
			::= { hmWanMbusCC 55 }

hmWanMbusCCVIF19		OBJECT-TYPE
			SYNTAX	INTEGER
			MAX-ACCESS	read-only
			STATUS	current
			::= { hmWanMbusCC 56 }

hmWanMbusCCValue19		OBJECT-TYPE
			SYNTAX	INTEGER
			MAX-ACCESS	read-only
			STATUS	current
			::= { hmWanMbusCC 57 }

hmWanMbusCCVIF1A		OBJECT-TYPE
			SYNTAX	INTEGER
			MAX-ACCESS	read-only
			STATUS	current
			::= { hmWanMbusCC 58 }

hmWanMbusCCValue1A		OBJECT-TYPE
			SYNTAX	INTEGER
			MAX-ACCESS	read-only
			STATUS	current
			::= { hmWanMbusCC 59 }

hmWanMbusCCVIF1B		OBJECT-TYPE
			SYNTAX	INTEGER
			MAX-ACCESS	read-only
			STATUS	current
			::= { hmWanMbusCC 60 }

hmWanMbusCCValue1B		OBJECT-TYPE
			SYNTAX	INTEGER
			MAX-ACCESS	read-only
			STATUS	current
			::= { hmWanMbusCC 61 }

hmWanMbusCCVIF1C		OBJECT-TYPE
			SYNTAX	INTEGER
			MAX-ACCESS	read-only
			STATUS	current
			::= { hmWanMbusCC 62 }

hmWanMbusCCValue1C		OBJECT-TYPE
			SYNTAX	INTEGER
			MAX-ACCESS	read-only
			STATUS	current
			::= { hmWanMbusCC 63 }

hmWanMbusCCVIF1D		OBJECT-TYPE
			SYNTAX	INTEGER
			MAX-ACCESS	read-only
			STATUS	current
			::= { hmWanMbusCC 64 }

hmWanMbusCCValue1D		OBJECT-TYPE
			SYNTAX	INTEGER
			MAX-ACCESS	read-only
			STATUS	current
			::= { hmWanMbusCC 65 }

hmWanMbusCCVIF1E		OBJECT-TYPE
			SYNTAX	INTEGER
			MAX-ACCESS	read-only
			STATUS	current
			::= { hmWanMbusCC 66 }

hmWanMbusCCValue1E		OBJECT-TYPE
			SYNTAX	INTEGER
			MAX-ACCESS	read-only
			STATUS	current
			::= { hmWanMbusCC 67 }

hmWanMbusCCVIF1F		OBJECT-TYPE
			SYNTAX	INTEGER
			MAX-ACCESS	read-only
			STATUS	current
			::= { hmWanMbusCC 68 }

hmWanMbusCCValue1F		OBJECT-TYPE
			SYNTAX	INTEGER
			MAX-ACCESS	read-only
			STATUS	current
			::= { hmWanMbusCC 69 }

hmWanMbusCCVIF20		OBJECT-TYPE
			SYNTAX	INTEGER
			MAX-ACCESS	read-only
			STATUS	current
			::= { hmWanMbusCC 70 }

hmWanMbusCCValue20		OBJECT-TYPE
			SYNTAX	INTEGER
			MAX-ACCESS	read-only
			STATUS	current
			::= { hmWanMbusCC 71 }

hmWanMbusCCVIF21		OBJECT-TYPE
			SYNTAX	INTEGER
			MAX-ACCESS	read-only
			STATUS	current
			::= { hmWanMbusCC 72 }

hmWanMbusCCValue21		OBJECT-TYPE
			SYNTAX	INTEGER
			MAX-ACCESS	read-only
			STATUS	current
			::= { hmWanMbusCC 73 }

hmWanMbusCCVIF22		OBJECT-TYPE
			SYNTAX	INTEGER
			MAX-ACCESS	read-only
			STATUS	current
			::= { hmWanMbusCC 74 }

hmWanMbusCCValue22		OBJECT-TYPE
			SYNTAX	INTEGER
			MAX-ACCESS	read-only
			STATUS	current
			::= { hmWanMbusCC 75 }

hmWanMbusCCVIF23		OBJECT-TYPE
			SYNTAX	INTEGER
			MAX-ACCESS	read-only
			STATUS	current
			::= { hmWanMbusCC 76 }

hmWanMbusCCValue23		OBJECT-TYPE
			SYNTAX	INTEGER
			MAX-ACCESS	read-only
			STATUS	current
			::= { hmWanMbusCC 77 }

hmWanMbusCCVIF24		OBJECT-TYPE
			SYNTAX	INTEGER
			MAX-ACCESS	read-only
			STATUS	current
			::= { hmWanMbusCC 78 }

hmWanMbusCCValue24		OBJECT-TYPE
			SYNTAX	INTEGER
			MAX-ACCESS	read-only
			STATUS	current
			::= { hmWanMbusCC 79 }

hmWanMbusCCVIF25		OBJECT-TYPE
			SYNTAX	INTEGER
			MAX-ACCESS	read-only
			STATUS	current
			::= { hmWanMbusCC 80 }

hmWanMbusCCValue25		OBJECT-TYPE
			SYNTAX	INTEGER
			MAX-ACCESS	read-only
			STATUS	current
			::= { hmWanMbusCC 81 }

hmWanMbusCCVIF26		OBJECT-TYPE
			SYNTAX	INTEGER
			MAX-ACCESS	read-only
			STATUS	current
			::= { hmWanMbusCC 82 }

hmWanMbusCCValue26		OBJECT-TYPE
			SYNTAX	INTEGER
			MAX-ACCESS	read-only
			STATUS	current
			::= { hmWanMbusCC 83 }

hmWanMbusCCVIF27		OBJECT-TYPE
			SYNTAX	INTEGER
			MAX-ACCESS	read-only
			STATUS	current
			::= { hmWanMbusCC 84 }

hmWanMbusCCValue27		OBJECT-TYPE
			SYNTAX	INTEGER
			MAX-ACCESS	read-only
			STATUS	current
			::= { hmWanMbusCC 85 }

hmWanMbusCCVIF28		OBJECT-TYPE
			SYNTAX	INTEGER
			MAX-ACCESS	read-only
			STATUS	current
			::= { hmWanMbusCC 86 }

hmWanMbusCCValue28		OBJECT-TYPE
			SYNTAX	INTEGER
			MAX-ACCESS	read-only
			STATUS	current
			::= { hmWanMbusCC 87 }

hmWanMbusCCVIF29		OBJECT-TYPE
			SYNTAX	INTEGER
			MAX-ACCESS	read-only
			STATUS	current
			::= { hmWanMbusCC 88 }

hmWanMbusCCValue29		OBJECT-TYPE
			SYNTAX	INTEGER
			MAX-ACCESS	read-only
			STATUS	current
			::= { hmWanMbusCC 89 }

hmWanMbusCCVIF2A		OBJECT-TYPE
			SYNTAX	INTEGER
			MAX-ACCESS	read-only
			STATUS	current
			::= { hmWanMbusCC 90 }

hmWanMbusCCValue2A		OBJECT-TYPE
			SYNTAX	INTEGER
			MAX-ACCESS	read-only
			STATUS	current
			::= { hmWanMbusCC 91 }

hmWanMbusCCVIF2B		OBJECT-TYPE
			SYNTAX	INTEGER
			MAX-ACCESS	read-only
			STATUS	current
			::= { hmWanMbusCC 92 }

hmWanMbusCCValue2B		OBJECT-TYPE
			SYNTAX	INTEGER
			MAX-ACCESS	read-only
			STATUS	current
			::= { hmWanMbusCC 93 }

hmWanMbusCCVIF2C		OBJECT-TYPE
			SYNTAX	INTEGER
			MAX-ACCESS	read-only
			STATUS	current
			::= { hmWanMbusCC 94 }

hmWanMbusCCValue2C		OBJECT-TYPE
			SYNTAX	INTEGER
			MAX-ACCESS	read-only
			STATUS	current
			::= { hmWanMbusCC 95 }

hmWanMbusCCVIF2D		OBJECT-TYPE
			SYNTAX	INTEGER
			MAX-ACCESS	read-only
			STATUS	current
			::= { hmWanMbusCC 96 }

hmWanMbusCCValue2D		OBJECT-TYPE
			SYNTAX	INTEGER
			MAX-ACCESS	read-only
			STATUS	current
			::= { hmWanMbusCC 97 }

hmWanMbusCCVIF2E		OBJECT-TYPE
			SYNTAX	INTEGER
			MAX-ACCESS	read-only
			STATUS	current
			::= { hmWanMbusCC 98 }

hmWanMbusCCValue2E		OBJECT-TYPE
			SYNTAX	INTEGER
			MAX-ACCESS	read-only
			STATUS	current
			::= { hmWanMbusCC 99 }

hmWanMbusCCVIF2F		OBJECT-TYPE
			SYNTAX	INTEGER
			MAX-ACCESS	read-only
			STATUS	current
			::= { hmWanMbusCC 100 }

hmWanMbusCCValue2F		OBJECT-TYPE
			SYNTAX	INTEGER
			MAX-ACCESS	read-only
			STATUS	current
			::= { hmWanMbusCC 101 }

hmWanMbusCD			OBJECT IDENTIFIER ::= { hmWanMbus 205 }

hmWanMbusCDIdNumber		OBJECT-TYPE
			SYNTAX	Gauge32
			MAX-ACCESS	read-only
			STATUS	current
			::= { hmWanMbusCD 1 }

hmWanMbusCDManufacturer	OBJECT-TYPE
			SYNTAX	Gauge32
			MAX-ACCESS	read-only
			STATUS	current
			::= { hmWanMbusCD 2 }

hmWanMbusCDVersion		OBJECT-TYPE
			SYNTAX	Gauge32
			MAX-ACCESS	read-only
			STATUS	current
			::= { hmWanMbusCD 3 }

hmWanMbusCDMedium		OBJECT-TYPE
			SYNTAX	Gauge32
			MAX-ACCESS	read-only
			STATUS	current
			::= { hmWanMbusCD 4 }

hmWanMbusCDStatus		OBJECT-TYPE
			SYNTAX	Gauge32
			MAX-ACCESS	read-only
			STATUS	current
			::= { hmWanMbusCD 5 }

hmWanMbusCDVIF00		OBJECT-TYPE
			SYNTAX	INTEGER
			MAX-ACCESS	read-only
			STATUS	current
			::= { hmWanMbusCD 6 }

hmWanMbusCDValue00		OBJECT-TYPE
			SYNTAX	INTEGER
			MAX-ACCESS	read-only
			STATUS	current
			::= { hmWanMbusCD 7 }

hmWanMbusCDVIF01		OBJECT-TYPE
			SYNTAX	INTEGER
			MAX-ACCESS	read-only
			STATUS	current
			::= { hmWanMbusCD 8 }

hmWanMbusCDValue01		OBJECT-TYPE
			SYNTAX	INTEGER
			MAX-ACCESS	read-only
			STATUS	current
			::= { hmWanMbusCD 9 }

hmWanMbusCDVIF02		OBJECT-TYPE
			SYNTAX	INTEGER
			MAX-ACCESS	read-only
			STATUS	current
			::= { hmWanMbusCD 10 }

hmWanMbusCDValue02		OBJECT-TYPE
			SYNTAX	INTEGER
			MAX-ACCESS	read-only
			STATUS	current
			::= { hmWanMbusCD 11 }

hmWanMbusCDVIF03		OBJECT-TYPE
			SYNTAX	INTEGER
			MAX-ACCESS	read-only
			STATUS	current
			::= { hmWanMbusCD 12 }

hmWanMbusCDValue03		OBJECT-TYPE
			SYNTAX	INTEGER
			MAX-ACCESS	read-only
			STATUS	current
			::= { hmWanMbusCD 13 }

hmWanMbusCDVIF04		OBJECT-TYPE
			SYNTAX	INTEGER
			MAX-ACCESS	read-only
			STATUS	current
			::= { hmWanMbusCD 14 }

hmWanMbusCDValue04		OBJECT-TYPE
			SYNTAX	INTEGER
			MAX-ACCESS	read-only
			STATUS	current
			::= { hmWanMbusCD 15 }

hmWanMbusCDVIF05		OBJECT-TYPE
			SYNTAX	INTEGER
			MAX-ACCESS	read-only
			STATUS	current
			::= { hmWanMbusCD 16 }

hmWanMbusCDValue05		OBJECT-TYPE
			SYNTAX	INTEGER
			MAX-ACCESS	read-only
			STATUS	current
			::= { hmWanMbusCD 17 }

hmWanMbusCDVIF06		OBJECT-TYPE
			SYNTAX	INTEGER
			MAX-ACCESS	read-only
			STATUS	current
			::= { hmWanMbusCD 18 }

hmWanMbusCDValue06		OBJECT-TYPE
			SYNTAX	INTEGER
			MAX-ACCESS	read-only
			STATUS	current
			::= { hmWanMbusCD 19 }

hmWanMbusCDVIF07		OBJECT-TYPE
			SYNTAX	INTEGER
			MAX-ACCESS	read-only
			STATUS	current
			::= { hmWanMbusCD 20 }

hmWanMbusCDValue07		OBJECT-TYPE
			SYNTAX	INTEGER
			MAX-ACCESS	read-only
			STATUS	current
			::= { hmWanMbusCD 21 }

hmWanMbusCDVIF08		OBJECT-TYPE
			SYNTAX	INTEGER
			MAX-ACCESS	read-only
			STATUS	current
			::= { hmWanMbusCD 22 }

hmWanMbusCDValue08		OBJECT-TYPE
			SYNTAX	INTEGER
			MAX-ACCESS	read-only
			STATUS	current
			::= { hmWanMbusCD 23 }

hmWanMbusCDVIF09		OBJECT-TYPE
			SYNTAX	INTEGER
			MAX-ACCESS	read-only
			STATUS	current
			::= { hmWanMbusCD 24 }

hmWanMbusCDValue09		OBJECT-TYPE
			SYNTAX	INTEGER
			MAX-ACCESS	read-only
			STATUS	current
			::= { hmWanMbusCD 25 }

hmWanMbusCDVIF0A		OBJECT-TYPE
			SYNTAX	INTEGER
			MAX-ACCESS	read-only
			STATUS	current
			::= { hmWanMbusCD 26 }

hmWanMbusCDValue0A		OBJECT-TYPE
			SYNTAX	INTEGER
			MAX-ACCESS	read-only
			STATUS	current
			::= { hmWanMbusCD 27 }

hmWanMbusCDVIF0B		OBJECT-TYPE
			SYNTAX	INTEGER
			MAX-ACCESS	read-only
			STATUS	current
			::= { hmWanMbusCD 28 }

hmWanMbusCDValue0B		OBJECT-TYPE
			SYNTAX	INTEGER
			MAX-ACCESS	read-only
			STATUS	current
			::= { hmWanMbusCD 29 }

hmWanMbusCDVIF0C		OBJECT-TYPE
			SYNTAX	INTEGER
			MAX-ACCESS	read-only
			STATUS	current
			::= { hmWanMbusCD 30 }

hmWanMbusCDValue0C		OBJECT-TYPE
			SYNTAX	INTEGER
			MAX-ACCESS	read-only
			STATUS	current
			::= { hmWanMbusCD 31 }

hmWanMbusCDVIF0D		OBJECT-TYPE
			SYNTAX	INTEGER
			MAX-ACCESS	read-only
			STATUS	current
			::= { hmWanMbusCD 32 }

hmWanMbusCDValue0D		OBJECT-TYPE
			SYNTAX	INTEGER
			MAX-ACCESS	read-only
			STATUS	current
			::= { hmWanMbusCD 33 }

hmWanMbusCDVIF0E		OBJECT-TYPE
			SYNTAX	INTEGER
			MAX-ACCESS	read-only
			STATUS	current
			::= { hmWanMbusCD 34 }

hmWanMbusCDValue0E		OBJECT-TYPE
			SYNTAX	INTEGER
			MAX-ACCESS	read-only
			STATUS	current
			::= { hmWanMbusCD 35 }

hmWanMbusCDVIF0F		OBJECT-TYPE
			SYNTAX	INTEGER
			MAX-ACCESS	read-only
			STATUS	current
			::= { hmWanMbusCD 36 }

hmWanMbusCDValue0F		OBJECT-TYPE
			SYNTAX	INTEGER
			MAX-ACCESS	read-only
			STATUS	current
			::= { hmWanMbusCD 37 }

hmWanMbusCDVIF10		OBJECT-TYPE
			SYNTAX	INTEGER
			MAX-ACCESS	read-only
			STATUS	current
			::= { hmWanMbusCD 38 }

hmWanMbusCDValue10		OBJECT-TYPE
			SYNTAX	INTEGER
			MAX-ACCESS	read-only
			STATUS	current
			::= { hmWanMbusCD 39 }

hmWanMbusCDVIF11		OBJECT-TYPE
			SYNTAX	INTEGER
			MAX-ACCESS	read-only
			STATUS	current
			::= { hmWanMbusCD 40 }

hmWanMbusCDValue11		OBJECT-TYPE
			SYNTAX	INTEGER
			MAX-ACCESS	read-only
			STATUS	current
			::= { hmWanMbusCD 41 }

hmWanMbusCDVIF12		OBJECT-TYPE
			SYNTAX	INTEGER
			MAX-ACCESS	read-only
			STATUS	current
			::= { hmWanMbusCD 42 }

hmWanMbusCDValue12		OBJECT-TYPE
			SYNTAX	INTEGER
			MAX-ACCESS	read-only
			STATUS	current
			::= { hmWanMbusCD 43 }

hmWanMbusCDVIF13		OBJECT-TYPE
			SYNTAX	INTEGER
			MAX-ACCESS	read-only
			STATUS	current
			::= { hmWanMbusCD 44 }

hmWanMbusCDValue13		OBJECT-TYPE
			SYNTAX	INTEGER
			MAX-ACCESS	read-only
			STATUS	current
			::= { hmWanMbusCD 45 }

hmWanMbusCDVIF14		OBJECT-TYPE
			SYNTAX	INTEGER
			MAX-ACCESS	read-only
			STATUS	current
			::= { hmWanMbusCD 46 }

hmWanMbusCDValue14		OBJECT-TYPE
			SYNTAX	INTEGER
			MAX-ACCESS	read-only
			STATUS	current
			::= { hmWanMbusCD 47 }

hmWanMbusCDVIF15		OBJECT-TYPE
			SYNTAX	INTEGER
			MAX-ACCESS	read-only
			STATUS	current
			::= { hmWanMbusCD 48 }

hmWanMbusCDValue15		OBJECT-TYPE
			SYNTAX	INTEGER
			MAX-ACCESS	read-only
			STATUS	current
			::= { hmWanMbusCD 49 }

hmWanMbusCDVIF16		OBJECT-TYPE
			SYNTAX	INTEGER
			MAX-ACCESS	read-only
			STATUS	current
			::= { hmWanMbusCD 50 }

hmWanMbusCDValue16		OBJECT-TYPE
			SYNTAX	INTEGER
			MAX-ACCESS	read-only
			STATUS	current
			::= { hmWanMbusCD 51 }

hmWanMbusCDVIF17		OBJECT-TYPE
			SYNTAX	INTEGER
			MAX-ACCESS	read-only
			STATUS	current
			::= { hmWanMbusCD 52 }

hmWanMbusCDValue17		OBJECT-TYPE
			SYNTAX	INTEGER
			MAX-ACCESS	read-only
			STATUS	current
			::= { hmWanMbusCD 53 }

hmWanMbusCDVIF18		OBJECT-TYPE
			SYNTAX	INTEGER
			MAX-ACCESS	read-only
			STATUS	current
			::= { hmWanMbusCD 54 }

hmWanMbusCDValue18		OBJECT-TYPE
			SYNTAX	INTEGER
			MAX-ACCESS	read-only
			STATUS	current
			::= { hmWanMbusCD 55 }

hmWanMbusCDVIF19		OBJECT-TYPE
			SYNTAX	INTEGER
			MAX-ACCESS	read-only
			STATUS	current
			::= { hmWanMbusCD 56 }

hmWanMbusCDValue19		OBJECT-TYPE
			SYNTAX	INTEGER
			MAX-ACCESS	read-only
			STATUS	current
			::= { hmWanMbusCD 57 }

hmWanMbusCDVIF1A		OBJECT-TYPE
			SYNTAX	INTEGER
			MAX-ACCESS	read-only
			STATUS	current
			::= { hmWanMbusCD 58 }

hmWanMbusCDValue1A		OBJECT-TYPE
			SYNTAX	INTEGER
			MAX-ACCESS	read-only
			STATUS	current
			::= { hmWanMbusCD 59 }

hmWanMbusCDVIF1B		OBJECT-TYPE
			SYNTAX	INTEGER
			MAX-ACCESS	read-only
			STATUS	current
			::= { hmWanMbusCD 60 }

hmWanMbusCDValue1B		OBJECT-TYPE
			SYNTAX	INTEGER
			MAX-ACCESS	read-only
			STATUS	current
			::= { hmWanMbusCD 61 }

hmWanMbusCDVIF1C		OBJECT-TYPE
			SYNTAX	INTEGER
			MAX-ACCESS	read-only
			STATUS	current
			::= { hmWanMbusCD 62 }

hmWanMbusCDValue1C		OBJECT-TYPE
			SYNTAX	INTEGER
			MAX-ACCESS	read-only
			STATUS	current
			::= { hmWanMbusCD 63 }

hmWanMbusCDVIF1D		OBJECT-TYPE
			SYNTAX	INTEGER
			MAX-ACCESS	read-only
			STATUS	current
			::= { hmWanMbusCD 64 }

hmWanMbusCDValue1D		OBJECT-TYPE
			SYNTAX	INTEGER
			MAX-ACCESS	read-only
			STATUS	current
			::= { hmWanMbusCD 65 }

hmWanMbusCDVIF1E		OBJECT-TYPE
			SYNTAX	INTEGER
			MAX-ACCESS	read-only
			STATUS	current
			::= { hmWanMbusCD 66 }

hmWanMbusCDValue1E		OBJECT-TYPE
			SYNTAX	INTEGER
			MAX-ACCESS	read-only
			STATUS	current
			::= { hmWanMbusCD 67 }

hmWanMbusCDVIF1F		OBJECT-TYPE
			SYNTAX	INTEGER
			MAX-ACCESS	read-only
			STATUS	current
			::= { hmWanMbusCD 68 }

hmWanMbusCDValue1F		OBJECT-TYPE
			SYNTAX	INTEGER
			MAX-ACCESS	read-only
			STATUS	current
			::= { hmWanMbusCD 69 }

hmWanMbusCDVIF20		OBJECT-TYPE
			SYNTAX	INTEGER
			MAX-ACCESS	read-only
			STATUS	current
			::= { hmWanMbusCD 70 }

hmWanMbusCDValue20		OBJECT-TYPE
			SYNTAX	INTEGER
			MAX-ACCESS	read-only
			STATUS	current
			::= { hmWanMbusCD 71 }

hmWanMbusCDVIF21		OBJECT-TYPE
			SYNTAX	INTEGER
			MAX-ACCESS	read-only
			STATUS	current
			::= { hmWanMbusCD 72 }

hmWanMbusCDValue21		OBJECT-TYPE
			SYNTAX	INTEGER
			MAX-ACCESS	read-only
			STATUS	current
			::= { hmWanMbusCD 73 }

hmWanMbusCDVIF22		OBJECT-TYPE
			SYNTAX	INTEGER
			MAX-ACCESS	read-only
			STATUS	current
			::= { hmWanMbusCD 74 }

hmWanMbusCDValue22		OBJECT-TYPE
			SYNTAX	INTEGER
			MAX-ACCESS	read-only
			STATUS	current
			::= { hmWanMbusCD 75 }

hmWanMbusCDVIF23		OBJECT-TYPE
			SYNTAX	INTEGER
			MAX-ACCESS	read-only
			STATUS	current
			::= { hmWanMbusCD 76 }

hmWanMbusCDValue23		OBJECT-TYPE
			SYNTAX	INTEGER
			MAX-ACCESS	read-only
			STATUS	current
			::= { hmWanMbusCD 77 }

hmWanMbusCDVIF24		OBJECT-TYPE
			SYNTAX	INTEGER
			MAX-ACCESS	read-only
			STATUS	current
			::= { hmWanMbusCD 78 }

hmWanMbusCDValue24		OBJECT-TYPE
			SYNTAX	INTEGER
			MAX-ACCESS	read-only
			STATUS	current
			::= { hmWanMbusCD 79 }

hmWanMbusCDVIF25		OBJECT-TYPE
			SYNTAX	INTEGER
			MAX-ACCESS	read-only
			STATUS	current
			::= { hmWanMbusCD 80 }

hmWanMbusCDValue25		OBJECT-TYPE
			SYNTAX	INTEGER
			MAX-ACCESS	read-only
			STATUS	current
			::= { hmWanMbusCD 81 }

hmWanMbusCDVIF26		OBJECT-TYPE
			SYNTAX	INTEGER
			MAX-ACCESS	read-only
			STATUS	current
			::= { hmWanMbusCD 82 }

hmWanMbusCDValue26		OBJECT-TYPE
			SYNTAX	INTEGER
			MAX-ACCESS	read-only
			STATUS	current
			::= { hmWanMbusCD 83 }

hmWanMbusCDVIF27		OBJECT-TYPE
			SYNTAX	INTEGER
			MAX-ACCESS	read-only
			STATUS	current
			::= { hmWanMbusCD 84 }

hmWanMbusCDValue27		OBJECT-TYPE
			SYNTAX	INTEGER
			MAX-ACCESS	read-only
			STATUS	current
			::= { hmWanMbusCD 85 }

hmWanMbusCDVIF28		OBJECT-TYPE
			SYNTAX	INTEGER
			MAX-ACCESS	read-only
			STATUS	current
			::= { hmWanMbusCD 86 }

hmWanMbusCDValue28		OBJECT-TYPE
			SYNTAX	INTEGER
			MAX-ACCESS	read-only
			STATUS	current
			::= { hmWanMbusCD 87 }

hmWanMbusCDVIF29		OBJECT-TYPE
			SYNTAX	INTEGER
			MAX-ACCESS	read-only
			STATUS	current
			::= { hmWanMbusCD 88 }

hmWanMbusCDValue29		OBJECT-TYPE
			SYNTAX	INTEGER
			MAX-ACCESS	read-only
			STATUS	current
			::= { hmWanMbusCD 89 }

hmWanMbusCDVIF2A		OBJECT-TYPE
			SYNTAX	INTEGER
			MAX-ACCESS	read-only
			STATUS	current
			::= { hmWanMbusCD 90 }

hmWanMbusCDValue2A		OBJECT-TYPE
			SYNTAX	INTEGER
			MAX-ACCESS	read-only
			STATUS	current
			::= { hmWanMbusCD 91 }

hmWanMbusCDVIF2B		OBJECT-TYPE
			SYNTAX	INTEGER
			MAX-ACCESS	read-only
			STATUS	current
			::= { hmWanMbusCD 92 }

hmWanMbusCDValue2B		OBJECT-TYPE
			SYNTAX	INTEGER
			MAX-ACCESS	read-only
			STATUS	current
			::= { hmWanMbusCD 93 }

hmWanMbusCDVIF2C		OBJECT-TYPE
			SYNTAX	INTEGER
			MAX-ACCESS	read-only
			STATUS	current
			::= { hmWanMbusCD 94 }

hmWanMbusCDValue2C		OBJECT-TYPE
			SYNTAX	INTEGER
			MAX-ACCESS	read-only
			STATUS	current
			::= { hmWanMbusCD 95 }

hmWanMbusCDVIF2D		OBJECT-TYPE
			SYNTAX	INTEGER
			MAX-ACCESS	read-only
			STATUS	current
			::= { hmWanMbusCD 96 }

hmWanMbusCDValue2D		OBJECT-TYPE
			SYNTAX	INTEGER
			MAX-ACCESS	read-only
			STATUS	current
			::= { hmWanMbusCD 97 }

hmWanMbusCDVIF2E		OBJECT-TYPE
			SYNTAX	INTEGER
			MAX-ACCESS	read-only
			STATUS	current
			::= { hmWanMbusCD 98 }

hmWanMbusCDValue2E		OBJECT-TYPE
			SYNTAX	INTEGER
			MAX-ACCESS	read-only
			STATUS	current
			::= { hmWanMbusCD 99 }

hmWanMbusCDVIF2F		OBJECT-TYPE
			SYNTAX	INTEGER
			MAX-ACCESS	read-only
			STATUS	current
			::= { hmWanMbusCD 100 }

hmWanMbusCDValue2F		OBJECT-TYPE
			SYNTAX	INTEGER
			MAX-ACCESS	read-only
			STATUS	current
			::= { hmWanMbusCD 101 }

hmWanMbusCE			OBJECT IDENTIFIER ::= { hmWanMbus 206 }

hmWanMbusCEIdNumber		OBJECT-TYPE
			SYNTAX	Gauge32
			MAX-ACCESS	read-only
			STATUS	current
			::= { hmWanMbusCE 1 }

hmWanMbusCEManufacturer	OBJECT-TYPE
			SYNTAX	Gauge32
			MAX-ACCESS	read-only
			STATUS	current
			::= { hmWanMbusCE 2 }

hmWanMbusCEVersion		OBJECT-TYPE
			SYNTAX	Gauge32
			MAX-ACCESS	read-only
			STATUS	current
			::= { hmWanMbusCE 3 }

hmWanMbusCEMedium		OBJECT-TYPE
			SYNTAX	Gauge32
			MAX-ACCESS	read-only
			STATUS	current
			::= { hmWanMbusCE 4 }

hmWanMbusCEStatus		OBJECT-TYPE
			SYNTAX	Gauge32
			MAX-ACCESS	read-only
			STATUS	current
			::= { hmWanMbusCE 5 }

hmWanMbusCEVIF00		OBJECT-TYPE
			SYNTAX	INTEGER
			MAX-ACCESS	read-only
			STATUS	current
			::= { hmWanMbusCE 6 }

hmWanMbusCEValue00		OBJECT-TYPE
			SYNTAX	INTEGER
			MAX-ACCESS	read-only
			STATUS	current
			::= { hmWanMbusCE 7 }

hmWanMbusCEVIF01		OBJECT-TYPE
			SYNTAX	INTEGER
			MAX-ACCESS	read-only
			STATUS	current
			::= { hmWanMbusCE 8 }

hmWanMbusCEValue01		OBJECT-TYPE
			SYNTAX	INTEGER
			MAX-ACCESS	read-only
			STATUS	current
			::= { hmWanMbusCE 9 }

hmWanMbusCEVIF02		OBJECT-TYPE
			SYNTAX	INTEGER
			MAX-ACCESS	read-only
			STATUS	current
			::= { hmWanMbusCE 10 }

hmWanMbusCEValue02		OBJECT-TYPE
			SYNTAX	INTEGER
			MAX-ACCESS	read-only
			STATUS	current
			::= { hmWanMbusCE 11 }

hmWanMbusCEVIF03		OBJECT-TYPE
			SYNTAX	INTEGER
			MAX-ACCESS	read-only
			STATUS	current
			::= { hmWanMbusCE 12 }

hmWanMbusCEValue03		OBJECT-TYPE
			SYNTAX	INTEGER
			MAX-ACCESS	read-only
			STATUS	current
			::= { hmWanMbusCE 13 }

hmWanMbusCEVIF04		OBJECT-TYPE
			SYNTAX	INTEGER
			MAX-ACCESS	read-only
			STATUS	current
			::= { hmWanMbusCE 14 }

hmWanMbusCEValue04		OBJECT-TYPE
			SYNTAX	INTEGER
			MAX-ACCESS	read-only
			STATUS	current
			::= { hmWanMbusCE 15 }

hmWanMbusCEVIF05		OBJECT-TYPE
			SYNTAX	INTEGER
			MAX-ACCESS	read-only
			STATUS	current
			::= { hmWanMbusCE 16 }

hmWanMbusCEValue05		OBJECT-TYPE
			SYNTAX	INTEGER
			MAX-ACCESS	read-only
			STATUS	current
			::= { hmWanMbusCE 17 }

hmWanMbusCEVIF06		OBJECT-TYPE
			SYNTAX	INTEGER
			MAX-ACCESS	read-only
			STATUS	current
			::= { hmWanMbusCE 18 }

hmWanMbusCEValue06		OBJECT-TYPE
			SYNTAX	INTEGER
			MAX-ACCESS	read-only
			STATUS	current
			::= { hmWanMbusCE 19 }

hmWanMbusCEVIF07		OBJECT-TYPE
			SYNTAX	INTEGER
			MAX-ACCESS	read-only
			STATUS	current
			::= { hmWanMbusCE 20 }

hmWanMbusCEValue07		OBJECT-TYPE
			SYNTAX	INTEGER
			MAX-ACCESS	read-only
			STATUS	current
			::= { hmWanMbusCE 21 }

hmWanMbusCEVIF08		OBJECT-TYPE
			SYNTAX	INTEGER
			MAX-ACCESS	read-only
			STATUS	current
			::= { hmWanMbusCE 22 }

hmWanMbusCEValue08		OBJECT-TYPE
			SYNTAX	INTEGER
			MAX-ACCESS	read-only
			STATUS	current
			::= { hmWanMbusCE 23 }

hmWanMbusCEVIF09		OBJECT-TYPE
			SYNTAX	INTEGER
			MAX-ACCESS	read-only
			STATUS	current
			::= { hmWanMbusCE 24 }

hmWanMbusCEValue09		OBJECT-TYPE
			SYNTAX	INTEGER
			MAX-ACCESS	read-only
			STATUS	current
			::= { hmWanMbusCE 25 }

hmWanMbusCEVIF0A		OBJECT-TYPE
			SYNTAX	INTEGER
			MAX-ACCESS	read-only
			STATUS	current
			::= { hmWanMbusCE 26 }

hmWanMbusCEValue0A		OBJECT-TYPE
			SYNTAX	INTEGER
			MAX-ACCESS	read-only
			STATUS	current
			::= { hmWanMbusCE 27 }

hmWanMbusCEVIF0B		OBJECT-TYPE
			SYNTAX	INTEGER
			MAX-ACCESS	read-only
			STATUS	current
			::= { hmWanMbusCE 28 }

hmWanMbusCEValue0B		OBJECT-TYPE
			SYNTAX	INTEGER
			MAX-ACCESS	read-only
			STATUS	current
			::= { hmWanMbusCE 29 }

hmWanMbusCEVIF0C		OBJECT-TYPE
			SYNTAX	INTEGER
			MAX-ACCESS	read-only
			STATUS	current
			::= { hmWanMbusCE 30 }

hmWanMbusCEValue0C		OBJECT-TYPE
			SYNTAX	INTEGER
			MAX-ACCESS	read-only
			STATUS	current
			::= { hmWanMbusCE 31 }

hmWanMbusCEVIF0D		OBJECT-TYPE
			SYNTAX	INTEGER
			MAX-ACCESS	read-only
			STATUS	current
			::= { hmWanMbusCE 32 }

hmWanMbusCEValue0D		OBJECT-TYPE
			SYNTAX	INTEGER
			MAX-ACCESS	read-only
			STATUS	current
			::= { hmWanMbusCE 33 }

hmWanMbusCEVIF0E		OBJECT-TYPE
			SYNTAX	INTEGER
			MAX-ACCESS	read-only
			STATUS	current
			::= { hmWanMbusCE 34 }

hmWanMbusCEValue0E		OBJECT-TYPE
			SYNTAX	INTEGER
			MAX-ACCESS	read-only
			STATUS	current
			::= { hmWanMbusCE 35 }

hmWanMbusCEVIF0F		OBJECT-TYPE
			SYNTAX	INTEGER
			MAX-ACCESS	read-only
			STATUS	current
			::= { hmWanMbusCE 36 }

hmWanMbusCEValue0F		OBJECT-TYPE
			SYNTAX	INTEGER
			MAX-ACCESS	read-only
			STATUS	current
			::= { hmWanMbusCE 37 }

hmWanMbusCEVIF10		OBJECT-TYPE
			SYNTAX	INTEGER
			MAX-ACCESS	read-only
			STATUS	current
			::= { hmWanMbusCE 38 }

hmWanMbusCEValue10		OBJECT-TYPE
			SYNTAX	INTEGER
			MAX-ACCESS	read-only
			STATUS	current
			::= { hmWanMbusCE 39 }

hmWanMbusCEVIF11		OBJECT-TYPE
			SYNTAX	INTEGER
			MAX-ACCESS	read-only
			STATUS	current
			::= { hmWanMbusCE 40 }

hmWanMbusCEValue11		OBJECT-TYPE
			SYNTAX	INTEGER
			MAX-ACCESS	read-only
			STATUS	current
			::= { hmWanMbusCE 41 }

hmWanMbusCEVIF12		OBJECT-TYPE
			SYNTAX	INTEGER
			MAX-ACCESS	read-only
			STATUS	current
			::= { hmWanMbusCE 42 }

hmWanMbusCEValue12		OBJECT-TYPE
			SYNTAX	INTEGER
			MAX-ACCESS	read-only
			STATUS	current
			::= { hmWanMbusCE 43 }

hmWanMbusCEVIF13		OBJECT-TYPE
			SYNTAX	INTEGER
			MAX-ACCESS	read-only
			STATUS	current
			::= { hmWanMbusCE 44 }

hmWanMbusCEValue13		OBJECT-TYPE
			SYNTAX	INTEGER
			MAX-ACCESS	read-only
			STATUS	current
			::= { hmWanMbusCE 45 }

hmWanMbusCEVIF14		OBJECT-TYPE
			SYNTAX	INTEGER
			MAX-ACCESS	read-only
			STATUS	current
			::= { hmWanMbusCE 46 }

hmWanMbusCEValue14		OBJECT-TYPE
			SYNTAX	INTEGER
			MAX-ACCESS	read-only
			STATUS	current
			::= { hmWanMbusCE 47 }

hmWanMbusCEVIF15		OBJECT-TYPE
			SYNTAX	INTEGER
			MAX-ACCESS	read-only
			STATUS	current
			::= { hmWanMbusCE 48 }

hmWanMbusCEValue15		OBJECT-TYPE
			SYNTAX	INTEGER
			MAX-ACCESS	read-only
			STATUS	current
			::= { hmWanMbusCE 49 }

hmWanMbusCEVIF16		OBJECT-TYPE
			SYNTAX	INTEGER
			MAX-ACCESS	read-only
			STATUS	current
			::= { hmWanMbusCE 50 }

hmWanMbusCEValue16		OBJECT-TYPE
			SYNTAX	INTEGER
			MAX-ACCESS	read-only
			STATUS	current
			::= { hmWanMbusCE 51 }

hmWanMbusCEVIF17		OBJECT-TYPE
			SYNTAX	INTEGER
			MAX-ACCESS	read-only
			STATUS	current
			::= { hmWanMbusCE 52 }

hmWanMbusCEValue17		OBJECT-TYPE
			SYNTAX	INTEGER
			MAX-ACCESS	read-only
			STATUS	current
			::= { hmWanMbusCE 53 }

hmWanMbusCEVIF18		OBJECT-TYPE
			SYNTAX	INTEGER
			MAX-ACCESS	read-only
			STATUS	current
			::= { hmWanMbusCE 54 }

hmWanMbusCEValue18		OBJECT-TYPE
			SYNTAX	INTEGER
			MAX-ACCESS	read-only
			STATUS	current
			::= { hmWanMbusCE 55 }

hmWanMbusCEVIF19		OBJECT-TYPE
			SYNTAX	INTEGER
			MAX-ACCESS	read-only
			STATUS	current
			::= { hmWanMbusCE 56 }

hmWanMbusCEValue19		OBJECT-TYPE
			SYNTAX	INTEGER
			MAX-ACCESS	read-only
			STATUS	current
			::= { hmWanMbusCE 57 }

hmWanMbusCEVIF1A		OBJECT-TYPE
			SYNTAX	INTEGER
			MAX-ACCESS	read-only
			STATUS	current
			::= { hmWanMbusCE 58 }

hmWanMbusCEValue1A		OBJECT-TYPE
			SYNTAX	INTEGER
			MAX-ACCESS	read-only
			STATUS	current
			::= { hmWanMbusCE 59 }

hmWanMbusCEVIF1B		OBJECT-TYPE
			SYNTAX	INTEGER
			MAX-ACCESS	read-only
			STATUS	current
			::= { hmWanMbusCE 60 }

hmWanMbusCEValue1B		OBJECT-TYPE
			SYNTAX	INTEGER
			MAX-ACCESS	read-only
			STATUS	current
			::= { hmWanMbusCE 61 }

hmWanMbusCEVIF1C		OBJECT-TYPE
			SYNTAX	INTEGER
			MAX-ACCESS	read-only
			STATUS	current
			::= { hmWanMbusCE 62 }

hmWanMbusCEValue1C		OBJECT-TYPE
			SYNTAX	INTEGER
			MAX-ACCESS	read-only
			STATUS	current
			::= { hmWanMbusCE 63 }

hmWanMbusCEVIF1D		OBJECT-TYPE
			SYNTAX	INTEGER
			MAX-ACCESS	read-only
			STATUS	current
			::= { hmWanMbusCE 64 }

hmWanMbusCEValue1D		OBJECT-TYPE
			SYNTAX	INTEGER
			MAX-ACCESS	read-only
			STATUS	current
			::= { hmWanMbusCE 65 }

hmWanMbusCEVIF1E		OBJECT-TYPE
			SYNTAX	INTEGER
			MAX-ACCESS	read-only
			STATUS	current
			::= { hmWanMbusCE 66 }

hmWanMbusCEValue1E		OBJECT-TYPE
			SYNTAX	INTEGER
			MAX-ACCESS	read-only
			STATUS	current
			::= { hmWanMbusCE 67 }

hmWanMbusCEVIF1F		OBJECT-TYPE
			SYNTAX	INTEGER
			MAX-ACCESS	read-only
			STATUS	current
			::= { hmWanMbusCE 68 }

hmWanMbusCEValue1F		OBJECT-TYPE
			SYNTAX	INTEGER
			MAX-ACCESS	read-only
			STATUS	current
			::= { hmWanMbusCE 69 }

hmWanMbusCEVIF20		OBJECT-TYPE
			SYNTAX	INTEGER
			MAX-ACCESS	read-only
			STATUS	current
			::= { hmWanMbusCE 70 }

hmWanMbusCEValue20		OBJECT-TYPE
			SYNTAX	INTEGER
			MAX-ACCESS	read-only
			STATUS	current
			::= { hmWanMbusCE 71 }

hmWanMbusCEVIF21		OBJECT-TYPE
			SYNTAX	INTEGER
			MAX-ACCESS	read-only
			STATUS	current
			::= { hmWanMbusCE 72 }

hmWanMbusCEValue21		OBJECT-TYPE
			SYNTAX	INTEGER
			MAX-ACCESS	read-only
			STATUS	current
			::= { hmWanMbusCE 73 }

hmWanMbusCEVIF22		OBJECT-TYPE
			SYNTAX	INTEGER
			MAX-ACCESS	read-only
			STATUS	current
			::= { hmWanMbusCE 74 }

hmWanMbusCEValue22		OBJECT-TYPE
			SYNTAX	INTEGER
			MAX-ACCESS	read-only
			STATUS	current
			::= { hmWanMbusCE 75 }

hmWanMbusCEVIF23		OBJECT-TYPE
			SYNTAX	INTEGER
			MAX-ACCESS	read-only
			STATUS	current
			::= { hmWanMbusCE 76 }

hmWanMbusCEValue23		OBJECT-TYPE
			SYNTAX	INTEGER
			MAX-ACCESS	read-only
			STATUS	current
			::= { hmWanMbusCE 77 }

hmWanMbusCEVIF24		OBJECT-TYPE
			SYNTAX	INTEGER
			MAX-ACCESS	read-only
			STATUS	current
			::= { hmWanMbusCE 78 }

hmWanMbusCEValue24		OBJECT-TYPE
			SYNTAX	INTEGER
			MAX-ACCESS	read-only
			STATUS	current
			::= { hmWanMbusCE 79 }

hmWanMbusCEVIF25		OBJECT-TYPE
			SYNTAX	INTEGER
			MAX-ACCESS	read-only
			STATUS	current
			::= { hmWanMbusCE 80 }

hmWanMbusCEValue25		OBJECT-TYPE
			SYNTAX	INTEGER
			MAX-ACCESS	read-only
			STATUS	current
			::= { hmWanMbusCE 81 }

hmWanMbusCEVIF26		OBJECT-TYPE
			SYNTAX	INTEGER
			MAX-ACCESS	read-only
			STATUS	current
			::= { hmWanMbusCE 82 }

hmWanMbusCEValue26		OBJECT-TYPE
			SYNTAX	INTEGER
			MAX-ACCESS	read-only
			STATUS	current
			::= { hmWanMbusCE 83 }

hmWanMbusCEVIF27		OBJECT-TYPE
			SYNTAX	INTEGER
			MAX-ACCESS	read-only
			STATUS	current
			::= { hmWanMbusCE 84 }

hmWanMbusCEValue27		OBJECT-TYPE
			SYNTAX	INTEGER
			MAX-ACCESS	read-only
			STATUS	current
			::= { hmWanMbusCE 85 }

hmWanMbusCEVIF28		OBJECT-TYPE
			SYNTAX	INTEGER
			MAX-ACCESS	read-only
			STATUS	current
			::= { hmWanMbusCE 86 }

hmWanMbusCEValue28		OBJECT-TYPE
			SYNTAX	INTEGER
			MAX-ACCESS	read-only
			STATUS	current
			::= { hmWanMbusCE 87 }

hmWanMbusCEVIF29		OBJECT-TYPE
			SYNTAX	INTEGER
			MAX-ACCESS	read-only
			STATUS	current
			::= { hmWanMbusCE 88 }

hmWanMbusCEValue29		OBJECT-TYPE
			SYNTAX	INTEGER
			MAX-ACCESS	read-only
			STATUS	current
			::= { hmWanMbusCE 89 }

hmWanMbusCEVIF2A		OBJECT-TYPE
			SYNTAX	INTEGER
			MAX-ACCESS	read-only
			STATUS	current
			::= { hmWanMbusCE 90 }

hmWanMbusCEValue2A		OBJECT-TYPE
			SYNTAX	INTEGER
			MAX-ACCESS	read-only
			STATUS	current
			::= { hmWanMbusCE 91 }

hmWanMbusCEVIF2B		OBJECT-TYPE
			SYNTAX	INTEGER
			MAX-ACCESS	read-only
			STATUS	current
			::= { hmWanMbusCE 92 }

hmWanMbusCEValue2B		OBJECT-TYPE
			SYNTAX	INTEGER
			MAX-ACCESS	read-only
			STATUS	current
			::= { hmWanMbusCE 93 }

hmWanMbusCEVIF2C		OBJECT-TYPE
			SYNTAX	INTEGER
			MAX-ACCESS	read-only
			STATUS	current
			::= { hmWanMbusCE 94 }

hmWanMbusCEValue2C		OBJECT-TYPE
			SYNTAX	INTEGER
			MAX-ACCESS	read-only
			STATUS	current
			::= { hmWanMbusCE 95 }

hmWanMbusCEVIF2D		OBJECT-TYPE
			SYNTAX	INTEGER
			MAX-ACCESS	read-only
			STATUS	current
			::= { hmWanMbusCE 96 }

hmWanMbusCEValue2D		OBJECT-TYPE
			SYNTAX	INTEGER
			MAX-ACCESS	read-only
			STATUS	current
			::= { hmWanMbusCE 97 }

hmWanMbusCEVIF2E		OBJECT-TYPE
			SYNTAX	INTEGER
			MAX-ACCESS	read-only
			STATUS	current
			::= { hmWanMbusCE 98 }

hmWanMbusCEValue2E		OBJECT-TYPE
			SYNTAX	INTEGER
			MAX-ACCESS	read-only
			STATUS	current
			::= { hmWanMbusCE 99 }

hmWanMbusCEVIF2F		OBJECT-TYPE
			SYNTAX	INTEGER
			MAX-ACCESS	read-only
			STATUS	current
			::= { hmWanMbusCE 100 }

hmWanMbusCEValue2F		OBJECT-TYPE
			SYNTAX	INTEGER
			MAX-ACCESS	read-only
			STATUS	current
			::= { hmWanMbusCE 101 }

hmWanMbusCF			OBJECT IDENTIFIER ::= { hmWanMbus 207 }

hmWanMbusCFIdNumber		OBJECT-TYPE
			SYNTAX	Gauge32
			MAX-ACCESS	read-only
			STATUS	current
			::= { hmWanMbusCF 1 }

hmWanMbusCFManufacturer	OBJECT-TYPE
			SYNTAX	Gauge32
			MAX-ACCESS	read-only
			STATUS	current
			::= { hmWanMbusCF 2 }

hmWanMbusCFVersion		OBJECT-TYPE
			SYNTAX	Gauge32
			MAX-ACCESS	read-only
			STATUS	current
			::= { hmWanMbusCF 3 }

hmWanMbusCFMedium		OBJECT-TYPE
			SYNTAX	Gauge32
			MAX-ACCESS	read-only
			STATUS	current
			::= { hmWanMbusCF 4 }

hmWanMbusCFStatus		OBJECT-TYPE
			SYNTAX	Gauge32
			MAX-ACCESS	read-only
			STATUS	current
			::= { hmWanMbusCF 5 }

hmWanMbusCFVIF00		OBJECT-TYPE
			SYNTAX	INTEGER
			MAX-ACCESS	read-only
			STATUS	current
			::= { hmWanMbusCF 6 }

hmWanMbusCFValue00		OBJECT-TYPE
			SYNTAX	INTEGER
			MAX-ACCESS	read-only
			STATUS	current
			::= { hmWanMbusCF 7 }

hmWanMbusCFVIF01		OBJECT-TYPE
			SYNTAX	INTEGER
			MAX-ACCESS	read-only
			STATUS	current
			::= { hmWanMbusCF 8 }

hmWanMbusCFValue01		OBJECT-TYPE
			SYNTAX	INTEGER
			MAX-ACCESS	read-only
			STATUS	current
			::= { hmWanMbusCF 9 }

hmWanMbusCFVIF02		OBJECT-TYPE
			SYNTAX	INTEGER
			MAX-ACCESS	read-only
			STATUS	current
			::= { hmWanMbusCF 10 }

hmWanMbusCFValue02		OBJECT-TYPE
			SYNTAX	INTEGER
			MAX-ACCESS	read-only
			STATUS	current
			::= { hmWanMbusCF 11 }

hmWanMbusCFVIF03		OBJECT-TYPE
			SYNTAX	INTEGER
			MAX-ACCESS	read-only
			STATUS	current
			::= { hmWanMbusCF 12 }

hmWanMbusCFValue03		OBJECT-TYPE
			SYNTAX	INTEGER
			MAX-ACCESS	read-only
			STATUS	current
			::= { hmWanMbusCF 13 }

hmWanMbusCFVIF04		OBJECT-TYPE
			SYNTAX	INTEGER
			MAX-ACCESS	read-only
			STATUS	current
			::= { hmWanMbusCF 14 }

hmWanMbusCFValue04		OBJECT-TYPE
			SYNTAX	INTEGER
			MAX-ACCESS	read-only
			STATUS	current
			::= { hmWanMbusCF 15 }

hmWanMbusCFVIF05		OBJECT-TYPE
			SYNTAX	INTEGER
			MAX-ACCESS	read-only
			STATUS	current
			::= { hmWanMbusCF 16 }

hmWanMbusCFValue05		OBJECT-TYPE
			SYNTAX	INTEGER
			MAX-ACCESS	read-only
			STATUS	current
			::= { hmWanMbusCF 17 }

hmWanMbusCFVIF06		OBJECT-TYPE
			SYNTAX	INTEGER
			MAX-ACCESS	read-only
			STATUS	current
			::= { hmWanMbusCF 18 }

hmWanMbusCFValue06		OBJECT-TYPE
			SYNTAX	INTEGER
			MAX-ACCESS	read-only
			STATUS	current
			::= { hmWanMbusCF 19 }

hmWanMbusCFVIF07		OBJECT-TYPE
			SYNTAX	INTEGER
			MAX-ACCESS	read-only
			STATUS	current
			::= { hmWanMbusCF 20 }

hmWanMbusCFValue07		OBJECT-TYPE
			SYNTAX	INTEGER
			MAX-ACCESS	read-only
			STATUS	current
			::= { hmWanMbusCF 21 }

hmWanMbusCFVIF08		OBJECT-TYPE
			SYNTAX	INTEGER
			MAX-ACCESS	read-only
			STATUS	current
			::= { hmWanMbusCF 22 }

hmWanMbusCFValue08		OBJECT-TYPE
			SYNTAX	INTEGER
			MAX-ACCESS	read-only
			STATUS	current
			::= { hmWanMbusCF 23 }

hmWanMbusCFVIF09		OBJECT-TYPE
			SYNTAX	INTEGER
			MAX-ACCESS	read-only
			STATUS	current
			::= { hmWanMbusCF 24 }

hmWanMbusCFValue09		OBJECT-TYPE
			SYNTAX	INTEGER
			MAX-ACCESS	read-only
			STATUS	current
			::= { hmWanMbusCF 25 }

hmWanMbusCFVIF0A		OBJECT-TYPE
			SYNTAX	INTEGER
			MAX-ACCESS	read-only
			STATUS	current
			::= { hmWanMbusCF 26 }

hmWanMbusCFValue0A		OBJECT-TYPE
			SYNTAX	INTEGER
			MAX-ACCESS	read-only
			STATUS	current
			::= { hmWanMbusCF 27 }

hmWanMbusCFVIF0B		OBJECT-TYPE
			SYNTAX	INTEGER
			MAX-ACCESS	read-only
			STATUS	current
			::= { hmWanMbusCF 28 }

hmWanMbusCFValue0B		OBJECT-TYPE
			SYNTAX	INTEGER
			MAX-ACCESS	read-only
			STATUS	current
			::= { hmWanMbusCF 29 }

hmWanMbusCFVIF0C		OBJECT-TYPE
			SYNTAX	INTEGER
			MAX-ACCESS	read-only
			STATUS	current
			::= { hmWanMbusCF 30 }

hmWanMbusCFValue0C		OBJECT-TYPE
			SYNTAX	INTEGER
			MAX-ACCESS	read-only
			STATUS	current
			::= { hmWanMbusCF 31 }

hmWanMbusCFVIF0D		OBJECT-TYPE
			SYNTAX	INTEGER
			MAX-ACCESS	read-only
			STATUS	current
			::= { hmWanMbusCF 32 }

hmWanMbusCFValue0D		OBJECT-TYPE
			SYNTAX	INTEGER
			MAX-ACCESS	read-only
			STATUS	current
			::= { hmWanMbusCF 33 }

hmWanMbusCFVIF0E		OBJECT-TYPE
			SYNTAX	INTEGER
			MAX-ACCESS	read-only
			STATUS	current
			::= { hmWanMbusCF 34 }

hmWanMbusCFValue0E		OBJECT-TYPE
			SYNTAX	INTEGER
			MAX-ACCESS	read-only
			STATUS	current
			::= { hmWanMbusCF 35 }

hmWanMbusCFVIF0F		OBJECT-TYPE
			SYNTAX	INTEGER
			MAX-ACCESS	read-only
			STATUS	current
			::= { hmWanMbusCF 36 }

hmWanMbusCFValue0F		OBJECT-TYPE
			SYNTAX	INTEGER
			MAX-ACCESS	read-only
			STATUS	current
			::= { hmWanMbusCF 37 }

hmWanMbusCFVIF10		OBJECT-TYPE
			SYNTAX	INTEGER
			MAX-ACCESS	read-only
			STATUS	current
			::= { hmWanMbusCF 38 }

hmWanMbusCFValue10		OBJECT-TYPE
			SYNTAX	INTEGER
			MAX-ACCESS	read-only
			STATUS	current
			::= { hmWanMbusCF 39 }

hmWanMbusCFVIF11		OBJECT-TYPE
			SYNTAX	INTEGER
			MAX-ACCESS	read-only
			STATUS	current
			::= { hmWanMbusCF 40 }

hmWanMbusCFValue11		OBJECT-TYPE
			SYNTAX	INTEGER
			MAX-ACCESS	read-only
			STATUS	current
			::= { hmWanMbusCF 41 }

hmWanMbusCFVIF12		OBJECT-TYPE
			SYNTAX	INTEGER
			MAX-ACCESS	read-only
			STATUS	current
			::= { hmWanMbusCF 42 }

hmWanMbusCFValue12		OBJECT-TYPE
			SYNTAX	INTEGER
			MAX-ACCESS	read-only
			STATUS	current
			::= { hmWanMbusCF 43 }

hmWanMbusCFVIF13		OBJECT-TYPE
			SYNTAX	INTEGER
			MAX-ACCESS	read-only
			STATUS	current
			::= { hmWanMbusCF 44 }

hmWanMbusCFValue13		OBJECT-TYPE
			SYNTAX	INTEGER
			MAX-ACCESS	read-only
			STATUS	current
			::= { hmWanMbusCF 45 }

hmWanMbusCFVIF14		OBJECT-TYPE
			SYNTAX	INTEGER
			MAX-ACCESS	read-only
			STATUS	current
			::= { hmWanMbusCF 46 }

hmWanMbusCFValue14		OBJECT-TYPE
			SYNTAX	INTEGER
			MAX-ACCESS	read-only
			STATUS	current
			::= { hmWanMbusCF 47 }

hmWanMbusCFVIF15		OBJECT-TYPE
			SYNTAX	INTEGER
			MAX-ACCESS	read-only
			STATUS	current
			::= { hmWanMbusCF 48 }

hmWanMbusCFValue15		OBJECT-TYPE
			SYNTAX	INTEGER
			MAX-ACCESS	read-only
			STATUS	current
			::= { hmWanMbusCF 49 }

hmWanMbusCFVIF16		OBJECT-TYPE
			SYNTAX	INTEGER
			MAX-ACCESS	read-only
			STATUS	current
			::= { hmWanMbusCF 50 }

hmWanMbusCFValue16		OBJECT-TYPE
			SYNTAX	INTEGER
			MAX-ACCESS	read-only
			STATUS	current
			::= { hmWanMbusCF 51 }

hmWanMbusCFVIF17		OBJECT-TYPE
			SYNTAX	INTEGER
			MAX-ACCESS	read-only
			STATUS	current
			::= { hmWanMbusCF 52 }

hmWanMbusCFValue17		OBJECT-TYPE
			SYNTAX	INTEGER
			MAX-ACCESS	read-only
			STATUS	current
			::= { hmWanMbusCF 53 }

hmWanMbusCFVIF18		OBJECT-TYPE
			SYNTAX	INTEGER
			MAX-ACCESS	read-only
			STATUS	current
			::= { hmWanMbusCF 54 }

hmWanMbusCFValue18		OBJECT-TYPE
			SYNTAX	INTEGER
			MAX-ACCESS	read-only
			STATUS	current
			::= { hmWanMbusCF 55 }

hmWanMbusCFVIF19		OBJECT-TYPE
			SYNTAX	INTEGER
			MAX-ACCESS	read-only
			STATUS	current
			::= { hmWanMbusCF 56 }

hmWanMbusCFValue19		OBJECT-TYPE
			SYNTAX	INTEGER
			MAX-ACCESS	read-only
			STATUS	current
			::= { hmWanMbusCF 57 }

hmWanMbusCFVIF1A		OBJECT-TYPE
			SYNTAX	INTEGER
			MAX-ACCESS	read-only
			STATUS	current
			::= { hmWanMbusCF 58 }

hmWanMbusCFValue1A		OBJECT-TYPE
			SYNTAX	INTEGER
			MAX-ACCESS	read-only
			STATUS	current
			::= { hmWanMbusCF 59 }

hmWanMbusCFVIF1B		OBJECT-TYPE
			SYNTAX	INTEGER
			MAX-ACCESS	read-only
			STATUS	current
			::= { hmWanMbusCF 60 }

hmWanMbusCFValue1B		OBJECT-TYPE
			SYNTAX	INTEGER
			MAX-ACCESS	read-only
			STATUS	current
			::= { hmWanMbusCF 61 }

hmWanMbusCFVIF1C		OBJECT-TYPE
			SYNTAX	INTEGER
			MAX-ACCESS	read-only
			STATUS	current
			::= { hmWanMbusCF 62 }

hmWanMbusCFValue1C		OBJECT-TYPE
			SYNTAX	INTEGER
			MAX-ACCESS	read-only
			STATUS	current
			::= { hmWanMbusCF 63 }

hmWanMbusCFVIF1D		OBJECT-TYPE
			SYNTAX	INTEGER
			MAX-ACCESS	read-only
			STATUS	current
			::= { hmWanMbusCF 64 }

hmWanMbusCFValue1D		OBJECT-TYPE
			SYNTAX	INTEGER
			MAX-ACCESS	read-only
			STATUS	current
			::= { hmWanMbusCF 65 }

hmWanMbusCFVIF1E		OBJECT-TYPE
			SYNTAX	INTEGER
			MAX-ACCESS	read-only
			STATUS	current
			::= { hmWanMbusCF 66 }

hmWanMbusCFValue1E		OBJECT-TYPE
			SYNTAX	INTEGER
			MAX-ACCESS	read-only
			STATUS	current
			::= { hmWanMbusCF 67 }

hmWanMbusCFVIF1F		OBJECT-TYPE
			SYNTAX	INTEGER
			MAX-ACCESS	read-only
			STATUS	current
			::= { hmWanMbusCF 68 }

hmWanMbusCFValue1F		OBJECT-TYPE
			SYNTAX	INTEGER
			MAX-ACCESS	read-only
			STATUS	current
			::= { hmWanMbusCF 69 }

hmWanMbusCFVIF20		OBJECT-TYPE
			SYNTAX	INTEGER
			MAX-ACCESS	read-only
			STATUS	current
			::= { hmWanMbusCF 70 }

hmWanMbusCFValue20		OBJECT-TYPE
			SYNTAX	INTEGER
			MAX-ACCESS	read-only
			STATUS	current
			::= { hmWanMbusCF 71 }

hmWanMbusCFVIF21		OBJECT-TYPE
			SYNTAX	INTEGER
			MAX-ACCESS	read-only
			STATUS	current
			::= { hmWanMbusCF 72 }

hmWanMbusCFValue21		OBJECT-TYPE
			SYNTAX	INTEGER
			MAX-ACCESS	read-only
			STATUS	current
			::= { hmWanMbusCF 73 }

hmWanMbusCFVIF22		OBJECT-TYPE
			SYNTAX	INTEGER
			MAX-ACCESS	read-only
			STATUS	current
			::= { hmWanMbusCF 74 }

hmWanMbusCFValue22		OBJECT-TYPE
			SYNTAX	INTEGER
			MAX-ACCESS	read-only
			STATUS	current
			::= { hmWanMbusCF 75 }

hmWanMbusCFVIF23		OBJECT-TYPE
			SYNTAX	INTEGER
			MAX-ACCESS	read-only
			STATUS	current
			::= { hmWanMbusCF 76 }

hmWanMbusCFValue23		OBJECT-TYPE
			SYNTAX	INTEGER
			MAX-ACCESS	read-only
			STATUS	current
			::= { hmWanMbusCF 77 }

hmWanMbusCFVIF24		OBJECT-TYPE
			SYNTAX	INTEGER
			MAX-ACCESS	read-only
			STATUS	current
			::= { hmWanMbusCF 78 }

hmWanMbusCFValue24		OBJECT-TYPE
			SYNTAX	INTEGER
			MAX-ACCESS	read-only
			STATUS	current
			::= { hmWanMbusCF 79 }

hmWanMbusCFVIF25		OBJECT-TYPE
			SYNTAX	INTEGER
			MAX-ACCESS	read-only
			STATUS	current
			::= { hmWanMbusCF 80 }

hmWanMbusCFValue25		OBJECT-TYPE
			SYNTAX	INTEGER
			MAX-ACCESS	read-only
			STATUS	current
			::= { hmWanMbusCF 81 }

hmWanMbusCFVIF26		OBJECT-TYPE
			SYNTAX	INTEGER
			MAX-ACCESS	read-only
			STATUS	current
			::= { hmWanMbusCF 82 }

hmWanMbusCFValue26		OBJECT-TYPE
			SYNTAX	INTEGER
			MAX-ACCESS	read-only
			STATUS	current
			::= { hmWanMbusCF 83 }

hmWanMbusCFVIF27		OBJECT-TYPE
			SYNTAX	INTEGER
			MAX-ACCESS	read-only
			STATUS	current
			::= { hmWanMbusCF 84 }

hmWanMbusCFValue27		OBJECT-TYPE
			SYNTAX	INTEGER
			MAX-ACCESS	read-only
			STATUS	current
			::= { hmWanMbusCF 85 }

hmWanMbusCFVIF28		OBJECT-TYPE
			SYNTAX	INTEGER
			MAX-ACCESS	read-only
			STATUS	current
			::= { hmWanMbusCF 86 }

hmWanMbusCFValue28		OBJECT-TYPE
			SYNTAX	INTEGER
			MAX-ACCESS	read-only
			STATUS	current
			::= { hmWanMbusCF 87 }

hmWanMbusCFVIF29		OBJECT-TYPE
			SYNTAX	INTEGER
			MAX-ACCESS	read-only
			STATUS	current
			::= { hmWanMbusCF 88 }

hmWanMbusCFValue29		OBJECT-TYPE
			SYNTAX	INTEGER
			MAX-ACCESS	read-only
			STATUS	current
			::= { hmWanMbusCF 89 }

hmWanMbusCFVIF2A		OBJECT-TYPE
			SYNTAX	INTEGER
			MAX-ACCESS	read-only
			STATUS	current
			::= { hmWanMbusCF 90 }

hmWanMbusCFValue2A		OBJECT-TYPE
			SYNTAX	INTEGER
			MAX-ACCESS	read-only
			STATUS	current
			::= { hmWanMbusCF 91 }

hmWanMbusCFVIF2B		OBJECT-TYPE
			SYNTAX	INTEGER
			MAX-ACCESS	read-only
			STATUS	current
			::= { hmWanMbusCF 92 }

hmWanMbusCFValue2B		OBJECT-TYPE
			SYNTAX	INTEGER
			MAX-ACCESS	read-only
			STATUS	current
			::= { hmWanMbusCF 93 }

hmWanMbusCFVIF2C		OBJECT-TYPE
			SYNTAX	INTEGER
			MAX-ACCESS	read-only
			STATUS	current
			::= { hmWanMbusCF 94 }

hmWanMbusCFValue2C		OBJECT-TYPE
			SYNTAX	INTEGER
			MAX-ACCESS	read-only
			STATUS	current
			::= { hmWanMbusCF 95 }

hmWanMbusCFVIF2D		OBJECT-TYPE
			SYNTAX	INTEGER
			MAX-ACCESS	read-only
			STATUS	current
			::= { hmWanMbusCF 96 }

hmWanMbusCFValue2D		OBJECT-TYPE
			SYNTAX	INTEGER
			MAX-ACCESS	read-only
			STATUS	current
			::= { hmWanMbusCF 97 }

hmWanMbusCFVIF2E		OBJECT-TYPE
			SYNTAX	INTEGER
			MAX-ACCESS	read-only
			STATUS	current
			::= { hmWanMbusCF 98 }

hmWanMbusCFValue2E		OBJECT-TYPE
			SYNTAX	INTEGER
			MAX-ACCESS	read-only
			STATUS	current
			::= { hmWanMbusCF 99 }

hmWanMbusCFVIF2F		OBJECT-TYPE
			SYNTAX	INTEGER
			MAX-ACCESS	read-only
			STATUS	current
			::= { hmWanMbusCF 100 }

hmWanMbusCFValue2F		OBJECT-TYPE
			SYNTAX	INTEGER
			MAX-ACCESS	read-only
			STATUS	current
			::= { hmWanMbusCF 101 }

hmWanMbusD0			OBJECT IDENTIFIER ::= { hmWanMbus 208 }

hmWanMbusD0IdNumber		OBJECT-TYPE
			SYNTAX	Gauge32
			MAX-ACCESS	read-only
			STATUS	current
			::= { hmWanMbusD0 1 }

hmWanMbusD0Manufacturer	OBJECT-TYPE
			SYNTAX	Gauge32
			MAX-ACCESS	read-only
			STATUS	current
			::= { hmWanMbusD0 2 }

hmWanMbusD0Version		OBJECT-TYPE
			SYNTAX	Gauge32
			MAX-ACCESS	read-only
			STATUS	current
			::= { hmWanMbusD0 3 }

hmWanMbusD0Medium		OBJECT-TYPE
			SYNTAX	Gauge32
			MAX-ACCESS	read-only
			STATUS	current
			::= { hmWanMbusD0 4 }

hmWanMbusD0Status		OBJECT-TYPE
			SYNTAX	Gauge32
			MAX-ACCESS	read-only
			STATUS	current
			::= { hmWanMbusD0 5 }

hmWanMbusD0VIF00		OBJECT-TYPE
			SYNTAX	INTEGER
			MAX-ACCESS	read-only
			STATUS	current
			::= { hmWanMbusD0 6 }

hmWanMbusD0Value00		OBJECT-TYPE
			SYNTAX	INTEGER
			MAX-ACCESS	read-only
			STATUS	current
			::= { hmWanMbusD0 7 }

hmWanMbusD0VIF01		OBJECT-TYPE
			SYNTAX	INTEGER
			MAX-ACCESS	read-only
			STATUS	current
			::= { hmWanMbusD0 8 }

hmWanMbusD0Value01		OBJECT-TYPE
			SYNTAX	INTEGER
			MAX-ACCESS	read-only
			STATUS	current
			::= { hmWanMbusD0 9 }

hmWanMbusD0VIF02		OBJECT-TYPE
			SYNTAX	INTEGER
			MAX-ACCESS	read-only
			STATUS	current
			::= { hmWanMbusD0 10 }

hmWanMbusD0Value02		OBJECT-TYPE
			SYNTAX	INTEGER
			MAX-ACCESS	read-only
			STATUS	current
			::= { hmWanMbusD0 11 }

hmWanMbusD0VIF03		OBJECT-TYPE
			SYNTAX	INTEGER
			MAX-ACCESS	read-only
			STATUS	current
			::= { hmWanMbusD0 12 }

hmWanMbusD0Value03		OBJECT-TYPE
			SYNTAX	INTEGER
			MAX-ACCESS	read-only
			STATUS	current
			::= { hmWanMbusD0 13 }

hmWanMbusD0VIF04		OBJECT-TYPE
			SYNTAX	INTEGER
			MAX-ACCESS	read-only
			STATUS	current
			::= { hmWanMbusD0 14 }

hmWanMbusD0Value04		OBJECT-TYPE
			SYNTAX	INTEGER
			MAX-ACCESS	read-only
			STATUS	current
			::= { hmWanMbusD0 15 }

hmWanMbusD0VIF05		OBJECT-TYPE
			SYNTAX	INTEGER
			MAX-ACCESS	read-only
			STATUS	current
			::= { hmWanMbusD0 16 }

hmWanMbusD0Value05		OBJECT-TYPE
			SYNTAX	INTEGER
			MAX-ACCESS	read-only
			STATUS	current
			::= { hmWanMbusD0 17 }

hmWanMbusD0VIF06		OBJECT-TYPE
			SYNTAX	INTEGER
			MAX-ACCESS	read-only
			STATUS	current
			::= { hmWanMbusD0 18 }

hmWanMbusD0Value06		OBJECT-TYPE
			SYNTAX	INTEGER
			MAX-ACCESS	read-only
			STATUS	current
			::= { hmWanMbusD0 19 }

hmWanMbusD0VIF07		OBJECT-TYPE
			SYNTAX	INTEGER
			MAX-ACCESS	read-only
			STATUS	current
			::= { hmWanMbusD0 20 }

hmWanMbusD0Value07		OBJECT-TYPE
			SYNTAX	INTEGER
			MAX-ACCESS	read-only
			STATUS	current
			::= { hmWanMbusD0 21 }

hmWanMbusD0VIF08		OBJECT-TYPE
			SYNTAX	INTEGER
			MAX-ACCESS	read-only
			STATUS	current
			::= { hmWanMbusD0 22 }

hmWanMbusD0Value08		OBJECT-TYPE
			SYNTAX	INTEGER
			MAX-ACCESS	read-only
			STATUS	current
			::= { hmWanMbusD0 23 }

hmWanMbusD0VIF09		OBJECT-TYPE
			SYNTAX	INTEGER
			MAX-ACCESS	read-only
			STATUS	current
			::= { hmWanMbusD0 24 }

hmWanMbusD0Value09		OBJECT-TYPE
			SYNTAX	INTEGER
			MAX-ACCESS	read-only
			STATUS	current
			::= { hmWanMbusD0 25 }

hmWanMbusD0VIF0A		OBJECT-TYPE
			SYNTAX	INTEGER
			MAX-ACCESS	read-only
			STATUS	current
			::= { hmWanMbusD0 26 }

hmWanMbusD0Value0A		OBJECT-TYPE
			SYNTAX	INTEGER
			MAX-ACCESS	read-only
			STATUS	current
			::= { hmWanMbusD0 27 }

hmWanMbusD0VIF0B		OBJECT-TYPE
			SYNTAX	INTEGER
			MAX-ACCESS	read-only
			STATUS	current
			::= { hmWanMbusD0 28 }

hmWanMbusD0Value0B		OBJECT-TYPE
			SYNTAX	INTEGER
			MAX-ACCESS	read-only
			STATUS	current
			::= { hmWanMbusD0 29 }

hmWanMbusD0VIF0C		OBJECT-TYPE
			SYNTAX	INTEGER
			MAX-ACCESS	read-only
			STATUS	current
			::= { hmWanMbusD0 30 }

hmWanMbusD0Value0C		OBJECT-TYPE
			SYNTAX	INTEGER
			MAX-ACCESS	read-only
			STATUS	current
			::= { hmWanMbusD0 31 }

hmWanMbusD0VIF0D		OBJECT-TYPE
			SYNTAX	INTEGER
			MAX-ACCESS	read-only
			STATUS	current
			::= { hmWanMbusD0 32 }

hmWanMbusD0Value0D		OBJECT-TYPE
			SYNTAX	INTEGER
			MAX-ACCESS	read-only
			STATUS	current
			::= { hmWanMbusD0 33 }

hmWanMbusD0VIF0E		OBJECT-TYPE
			SYNTAX	INTEGER
			MAX-ACCESS	read-only
			STATUS	current
			::= { hmWanMbusD0 34 }

hmWanMbusD0Value0E		OBJECT-TYPE
			SYNTAX	INTEGER
			MAX-ACCESS	read-only
			STATUS	current
			::= { hmWanMbusD0 35 }

hmWanMbusD0VIF0F		OBJECT-TYPE
			SYNTAX	INTEGER
			MAX-ACCESS	read-only
			STATUS	current
			::= { hmWanMbusD0 36 }

hmWanMbusD0Value0F		OBJECT-TYPE
			SYNTAX	INTEGER
			MAX-ACCESS	read-only
			STATUS	current
			::= { hmWanMbusD0 37 }

hmWanMbusD0VIF10		OBJECT-TYPE
			SYNTAX	INTEGER
			MAX-ACCESS	read-only
			STATUS	current
			::= { hmWanMbusD0 38 }

hmWanMbusD0Value10		OBJECT-TYPE
			SYNTAX	INTEGER
			MAX-ACCESS	read-only
			STATUS	current
			::= { hmWanMbusD0 39 }

hmWanMbusD0VIF11		OBJECT-TYPE
			SYNTAX	INTEGER
			MAX-ACCESS	read-only
			STATUS	current
			::= { hmWanMbusD0 40 }

hmWanMbusD0Value11		OBJECT-TYPE
			SYNTAX	INTEGER
			MAX-ACCESS	read-only
			STATUS	current
			::= { hmWanMbusD0 41 }

hmWanMbusD0VIF12		OBJECT-TYPE
			SYNTAX	INTEGER
			MAX-ACCESS	read-only
			STATUS	current
			::= { hmWanMbusD0 42 }

hmWanMbusD0Value12		OBJECT-TYPE
			SYNTAX	INTEGER
			MAX-ACCESS	read-only
			STATUS	current
			::= { hmWanMbusD0 43 }

hmWanMbusD0VIF13		OBJECT-TYPE
			SYNTAX	INTEGER
			MAX-ACCESS	read-only
			STATUS	current
			::= { hmWanMbusD0 44 }

hmWanMbusD0Value13		OBJECT-TYPE
			SYNTAX	INTEGER
			MAX-ACCESS	read-only
			STATUS	current
			::= { hmWanMbusD0 45 }

hmWanMbusD0VIF14		OBJECT-TYPE
			SYNTAX	INTEGER
			MAX-ACCESS	read-only
			STATUS	current
			::= { hmWanMbusD0 46 }

hmWanMbusD0Value14		OBJECT-TYPE
			SYNTAX	INTEGER
			MAX-ACCESS	read-only
			STATUS	current
			::= { hmWanMbusD0 47 }

hmWanMbusD0VIF15		OBJECT-TYPE
			SYNTAX	INTEGER
			MAX-ACCESS	read-only
			STATUS	current
			::= { hmWanMbusD0 48 }

hmWanMbusD0Value15		OBJECT-TYPE
			SYNTAX	INTEGER
			MAX-ACCESS	read-only
			STATUS	current
			::= { hmWanMbusD0 49 }

hmWanMbusD0VIF16		OBJECT-TYPE
			SYNTAX	INTEGER
			MAX-ACCESS	read-only
			STATUS	current
			::= { hmWanMbusD0 50 }

hmWanMbusD0Value16		OBJECT-TYPE
			SYNTAX	INTEGER
			MAX-ACCESS	read-only
			STATUS	current
			::= { hmWanMbusD0 51 }

hmWanMbusD0VIF17		OBJECT-TYPE
			SYNTAX	INTEGER
			MAX-ACCESS	read-only
			STATUS	current
			::= { hmWanMbusD0 52 }

hmWanMbusD0Value17		OBJECT-TYPE
			SYNTAX	INTEGER
			MAX-ACCESS	read-only
			STATUS	current
			::= { hmWanMbusD0 53 }

hmWanMbusD0VIF18		OBJECT-TYPE
			SYNTAX	INTEGER
			MAX-ACCESS	read-only
			STATUS	current
			::= { hmWanMbusD0 54 }

hmWanMbusD0Value18		OBJECT-TYPE
			SYNTAX	INTEGER
			MAX-ACCESS	read-only
			STATUS	current
			::= { hmWanMbusD0 55 }

hmWanMbusD0VIF19		OBJECT-TYPE
			SYNTAX	INTEGER
			MAX-ACCESS	read-only
			STATUS	current
			::= { hmWanMbusD0 56 }

hmWanMbusD0Value19		OBJECT-TYPE
			SYNTAX	INTEGER
			MAX-ACCESS	read-only
			STATUS	current
			::= { hmWanMbusD0 57 }

hmWanMbusD0VIF1A		OBJECT-TYPE
			SYNTAX	INTEGER
			MAX-ACCESS	read-only
			STATUS	current
			::= { hmWanMbusD0 58 }

hmWanMbusD0Value1A		OBJECT-TYPE
			SYNTAX	INTEGER
			MAX-ACCESS	read-only
			STATUS	current
			::= { hmWanMbusD0 59 }

hmWanMbusD0VIF1B		OBJECT-TYPE
			SYNTAX	INTEGER
			MAX-ACCESS	read-only
			STATUS	current
			::= { hmWanMbusD0 60 }

hmWanMbusD0Value1B		OBJECT-TYPE
			SYNTAX	INTEGER
			MAX-ACCESS	read-only
			STATUS	current
			::= { hmWanMbusD0 61 }

hmWanMbusD0VIF1C		OBJECT-TYPE
			SYNTAX	INTEGER
			MAX-ACCESS	read-only
			STATUS	current
			::= { hmWanMbusD0 62 }

hmWanMbusD0Value1C		OBJECT-TYPE
			SYNTAX	INTEGER
			MAX-ACCESS	read-only
			STATUS	current
			::= { hmWanMbusD0 63 }

hmWanMbusD0VIF1D		OBJECT-TYPE
			SYNTAX	INTEGER
			MAX-ACCESS	read-only
			STATUS	current
			::= { hmWanMbusD0 64 }

hmWanMbusD0Value1D		OBJECT-TYPE
			SYNTAX	INTEGER
			MAX-ACCESS	read-only
			STATUS	current
			::= { hmWanMbusD0 65 }

hmWanMbusD0VIF1E		OBJECT-TYPE
			SYNTAX	INTEGER
			MAX-ACCESS	read-only
			STATUS	current
			::= { hmWanMbusD0 66 }

hmWanMbusD0Value1E		OBJECT-TYPE
			SYNTAX	INTEGER
			MAX-ACCESS	read-only
			STATUS	current
			::= { hmWanMbusD0 67 }

hmWanMbusD0VIF1F		OBJECT-TYPE
			SYNTAX	INTEGER
			MAX-ACCESS	read-only
			STATUS	current
			::= { hmWanMbusD0 68 }

hmWanMbusD0Value1F		OBJECT-TYPE
			SYNTAX	INTEGER
			MAX-ACCESS	read-only
			STATUS	current
			::= { hmWanMbusD0 69 }

hmWanMbusD0VIF20		OBJECT-TYPE
			SYNTAX	INTEGER
			MAX-ACCESS	read-only
			STATUS	current
			::= { hmWanMbusD0 70 }

hmWanMbusD0Value20		OBJECT-TYPE
			SYNTAX	INTEGER
			MAX-ACCESS	read-only
			STATUS	current
			::= { hmWanMbusD0 71 }

hmWanMbusD0VIF21		OBJECT-TYPE
			SYNTAX	INTEGER
			MAX-ACCESS	read-only
			STATUS	current
			::= { hmWanMbusD0 72 }

hmWanMbusD0Value21		OBJECT-TYPE
			SYNTAX	INTEGER
			MAX-ACCESS	read-only
			STATUS	current
			::= { hmWanMbusD0 73 }

hmWanMbusD0VIF22		OBJECT-TYPE
			SYNTAX	INTEGER
			MAX-ACCESS	read-only
			STATUS	current
			::= { hmWanMbusD0 74 }

hmWanMbusD0Value22		OBJECT-TYPE
			SYNTAX	INTEGER
			MAX-ACCESS	read-only
			STATUS	current
			::= { hmWanMbusD0 75 }

hmWanMbusD0VIF23		OBJECT-TYPE
			SYNTAX	INTEGER
			MAX-ACCESS	read-only
			STATUS	current
			::= { hmWanMbusD0 76 }

hmWanMbusD0Value23		OBJECT-TYPE
			SYNTAX	INTEGER
			MAX-ACCESS	read-only
			STATUS	current
			::= { hmWanMbusD0 77 }

hmWanMbusD0VIF24		OBJECT-TYPE
			SYNTAX	INTEGER
			MAX-ACCESS	read-only
			STATUS	current
			::= { hmWanMbusD0 78 }

hmWanMbusD0Value24		OBJECT-TYPE
			SYNTAX	INTEGER
			MAX-ACCESS	read-only
			STATUS	current
			::= { hmWanMbusD0 79 }

hmWanMbusD0VIF25		OBJECT-TYPE
			SYNTAX	INTEGER
			MAX-ACCESS	read-only
			STATUS	current
			::= { hmWanMbusD0 80 }

hmWanMbusD0Value25		OBJECT-TYPE
			SYNTAX	INTEGER
			MAX-ACCESS	read-only
			STATUS	current
			::= { hmWanMbusD0 81 }

hmWanMbusD0VIF26		OBJECT-TYPE
			SYNTAX	INTEGER
			MAX-ACCESS	read-only
			STATUS	current
			::= { hmWanMbusD0 82 }

hmWanMbusD0Value26		OBJECT-TYPE
			SYNTAX	INTEGER
			MAX-ACCESS	read-only
			STATUS	current
			::= { hmWanMbusD0 83 }

hmWanMbusD0VIF27		OBJECT-TYPE
			SYNTAX	INTEGER
			MAX-ACCESS	read-only
			STATUS	current
			::= { hmWanMbusD0 84 }

hmWanMbusD0Value27		OBJECT-TYPE
			SYNTAX	INTEGER
			MAX-ACCESS	read-only
			STATUS	current
			::= { hmWanMbusD0 85 }

hmWanMbusD0VIF28		OBJECT-TYPE
			SYNTAX	INTEGER
			MAX-ACCESS	read-only
			STATUS	current
			::= { hmWanMbusD0 86 }

hmWanMbusD0Value28		OBJECT-TYPE
			SYNTAX	INTEGER
			MAX-ACCESS	read-only
			STATUS	current
			::= { hmWanMbusD0 87 }

hmWanMbusD0VIF29		OBJECT-TYPE
			SYNTAX	INTEGER
			MAX-ACCESS	read-only
			STATUS	current
			::= { hmWanMbusD0 88 }

hmWanMbusD0Value29		OBJECT-TYPE
			SYNTAX	INTEGER
			MAX-ACCESS	read-only
			STATUS	current
			::= { hmWanMbusD0 89 }

hmWanMbusD0VIF2A		OBJECT-TYPE
			SYNTAX	INTEGER
			MAX-ACCESS	read-only
			STATUS	current
			::= { hmWanMbusD0 90 }

hmWanMbusD0Value2A		OBJECT-TYPE
			SYNTAX	INTEGER
			MAX-ACCESS	read-only
			STATUS	current
			::= { hmWanMbusD0 91 }

hmWanMbusD0VIF2B		OBJECT-TYPE
			SYNTAX	INTEGER
			MAX-ACCESS	read-only
			STATUS	current
			::= { hmWanMbusD0 92 }

hmWanMbusD0Value2B		OBJECT-TYPE
			SYNTAX	INTEGER
			MAX-ACCESS	read-only
			STATUS	current
			::= { hmWanMbusD0 93 }

hmWanMbusD0VIF2C		OBJECT-TYPE
			SYNTAX	INTEGER
			MAX-ACCESS	read-only
			STATUS	current
			::= { hmWanMbusD0 94 }

hmWanMbusD0Value2C		OBJECT-TYPE
			SYNTAX	INTEGER
			MAX-ACCESS	read-only
			STATUS	current
			::= { hmWanMbusD0 95 }

hmWanMbusD0VIF2D		OBJECT-TYPE
			SYNTAX	INTEGER
			MAX-ACCESS	read-only
			STATUS	current
			::= { hmWanMbusD0 96 }

hmWanMbusD0Value2D		OBJECT-TYPE
			SYNTAX	INTEGER
			MAX-ACCESS	read-only
			STATUS	current
			::= { hmWanMbusD0 97 }

hmWanMbusD0VIF2E		OBJECT-TYPE
			SYNTAX	INTEGER
			MAX-ACCESS	read-only
			STATUS	current
			::= { hmWanMbusD0 98 }

hmWanMbusD0Value2E		OBJECT-TYPE
			SYNTAX	INTEGER
			MAX-ACCESS	read-only
			STATUS	current
			::= { hmWanMbusD0 99 }

hmWanMbusD0VIF2F		OBJECT-TYPE
			SYNTAX	INTEGER
			MAX-ACCESS	read-only
			STATUS	current
			::= { hmWanMbusD0 100 }

hmWanMbusD0Value2F		OBJECT-TYPE
			SYNTAX	INTEGER
			MAX-ACCESS	read-only
			STATUS	current
			::= { hmWanMbusD0 101 }

hmWanMbusD1			OBJECT IDENTIFIER ::= { hmWanMbus 209 }

hmWanMbusD1IdNumber		OBJECT-TYPE
			SYNTAX	Gauge32
			MAX-ACCESS	read-only
			STATUS	current
			::= { hmWanMbusD1 1 }

hmWanMbusD1Manufacturer	OBJECT-TYPE
			SYNTAX	Gauge32
			MAX-ACCESS	read-only
			STATUS	current
			::= { hmWanMbusD1 2 }

hmWanMbusD1Version		OBJECT-TYPE
			SYNTAX	Gauge32
			MAX-ACCESS	read-only
			STATUS	current
			::= { hmWanMbusD1 3 }

hmWanMbusD1Medium		OBJECT-TYPE
			SYNTAX	Gauge32
			MAX-ACCESS	read-only
			STATUS	current
			::= { hmWanMbusD1 4 }

hmWanMbusD1Status		OBJECT-TYPE
			SYNTAX	Gauge32
			MAX-ACCESS	read-only
			STATUS	current
			::= { hmWanMbusD1 5 }

hmWanMbusD1VIF00		OBJECT-TYPE
			SYNTAX	INTEGER
			MAX-ACCESS	read-only
			STATUS	current
			::= { hmWanMbusD1 6 }

hmWanMbusD1Value00		OBJECT-TYPE
			SYNTAX	INTEGER
			MAX-ACCESS	read-only
			STATUS	current
			::= { hmWanMbusD1 7 }

hmWanMbusD1VIF01		OBJECT-TYPE
			SYNTAX	INTEGER
			MAX-ACCESS	read-only
			STATUS	current
			::= { hmWanMbusD1 8 }

hmWanMbusD1Value01		OBJECT-TYPE
			SYNTAX	INTEGER
			MAX-ACCESS	read-only
			STATUS	current
			::= { hmWanMbusD1 9 }

hmWanMbusD1VIF02		OBJECT-TYPE
			SYNTAX	INTEGER
			MAX-ACCESS	read-only
			STATUS	current
			::= { hmWanMbusD1 10 }

hmWanMbusD1Value02		OBJECT-TYPE
			SYNTAX	INTEGER
			MAX-ACCESS	read-only
			STATUS	current
			::= { hmWanMbusD1 11 }

hmWanMbusD1VIF03		OBJECT-TYPE
			SYNTAX	INTEGER
			MAX-ACCESS	read-only
			STATUS	current
			::= { hmWanMbusD1 12 }

hmWanMbusD1Value03		OBJECT-TYPE
			SYNTAX	INTEGER
			MAX-ACCESS	read-only
			STATUS	current
			::= { hmWanMbusD1 13 }

hmWanMbusD1VIF04		OBJECT-TYPE
			SYNTAX	INTEGER
			MAX-ACCESS	read-only
			STATUS	current
			::= { hmWanMbusD1 14 }

hmWanMbusD1Value04		OBJECT-TYPE
			SYNTAX	INTEGER
			MAX-ACCESS	read-only
			STATUS	current
			::= { hmWanMbusD1 15 }

hmWanMbusD1VIF05		OBJECT-TYPE
			SYNTAX	INTEGER
			MAX-ACCESS	read-only
			STATUS	current
			::= { hmWanMbusD1 16 }

hmWanMbusD1Value05		OBJECT-TYPE
			SYNTAX	INTEGER
			MAX-ACCESS	read-only
			STATUS	current
			::= { hmWanMbusD1 17 }

hmWanMbusD1VIF06		OBJECT-TYPE
			SYNTAX	INTEGER
			MAX-ACCESS	read-only
			STATUS	current
			::= { hmWanMbusD1 18 }

hmWanMbusD1Value06		OBJECT-TYPE
			SYNTAX	INTEGER
			MAX-ACCESS	read-only
			STATUS	current
			::= { hmWanMbusD1 19 }

hmWanMbusD1VIF07		OBJECT-TYPE
			SYNTAX	INTEGER
			MAX-ACCESS	read-only
			STATUS	current
			::= { hmWanMbusD1 20 }

hmWanMbusD1Value07		OBJECT-TYPE
			SYNTAX	INTEGER
			MAX-ACCESS	read-only
			STATUS	current
			::= { hmWanMbusD1 21 }

hmWanMbusD1VIF08		OBJECT-TYPE
			SYNTAX	INTEGER
			MAX-ACCESS	read-only
			STATUS	current
			::= { hmWanMbusD1 22 }

hmWanMbusD1Value08		OBJECT-TYPE
			SYNTAX	INTEGER
			MAX-ACCESS	read-only
			STATUS	current
			::= { hmWanMbusD1 23 }

hmWanMbusD1VIF09		OBJECT-TYPE
			SYNTAX	INTEGER
			MAX-ACCESS	read-only
			STATUS	current
			::= { hmWanMbusD1 24 }

hmWanMbusD1Value09		OBJECT-TYPE
			SYNTAX	INTEGER
			MAX-ACCESS	read-only
			STATUS	current
			::= { hmWanMbusD1 25 }

hmWanMbusD1VIF0A		OBJECT-TYPE
			SYNTAX	INTEGER
			MAX-ACCESS	read-only
			STATUS	current
			::= { hmWanMbusD1 26 }

hmWanMbusD1Value0A		OBJECT-TYPE
			SYNTAX	INTEGER
			MAX-ACCESS	read-only
			STATUS	current
			::= { hmWanMbusD1 27 }

hmWanMbusD1VIF0B		OBJECT-TYPE
			SYNTAX	INTEGER
			MAX-ACCESS	read-only
			STATUS	current
			::= { hmWanMbusD1 28 }

hmWanMbusD1Value0B		OBJECT-TYPE
			SYNTAX	INTEGER
			MAX-ACCESS	read-only
			STATUS	current
			::= { hmWanMbusD1 29 }

hmWanMbusD1VIF0C		OBJECT-TYPE
			SYNTAX	INTEGER
			MAX-ACCESS	read-only
			STATUS	current
			::= { hmWanMbusD1 30 }

hmWanMbusD1Value0C		OBJECT-TYPE
			SYNTAX	INTEGER
			MAX-ACCESS	read-only
			STATUS	current
			::= { hmWanMbusD1 31 }

hmWanMbusD1VIF0D		OBJECT-TYPE
			SYNTAX	INTEGER
			MAX-ACCESS	read-only
			STATUS	current
			::= { hmWanMbusD1 32 }

hmWanMbusD1Value0D		OBJECT-TYPE
			SYNTAX	INTEGER
			MAX-ACCESS	read-only
			STATUS	current
			::= { hmWanMbusD1 33 }

hmWanMbusD1VIF0E		OBJECT-TYPE
			SYNTAX	INTEGER
			MAX-ACCESS	read-only
			STATUS	current
			::= { hmWanMbusD1 34 }

hmWanMbusD1Value0E		OBJECT-TYPE
			SYNTAX	INTEGER
			MAX-ACCESS	read-only
			STATUS	current
			::= { hmWanMbusD1 35 }

hmWanMbusD1VIF0F		OBJECT-TYPE
			SYNTAX	INTEGER
			MAX-ACCESS	read-only
			STATUS	current
			::= { hmWanMbusD1 36 }

hmWanMbusD1Value0F		OBJECT-TYPE
			SYNTAX	INTEGER
			MAX-ACCESS	read-only
			STATUS	current
			::= { hmWanMbusD1 37 }

hmWanMbusD1VIF10		OBJECT-TYPE
			SYNTAX	INTEGER
			MAX-ACCESS	read-only
			STATUS	current
			::= { hmWanMbusD1 38 }

hmWanMbusD1Value10		OBJECT-TYPE
			SYNTAX	INTEGER
			MAX-ACCESS	read-only
			STATUS	current
			::= { hmWanMbusD1 39 }

hmWanMbusD1VIF11		OBJECT-TYPE
			SYNTAX	INTEGER
			MAX-ACCESS	read-only
			STATUS	current
			::= { hmWanMbusD1 40 }

hmWanMbusD1Value11		OBJECT-TYPE
			SYNTAX	INTEGER
			MAX-ACCESS	read-only
			STATUS	current
			::= { hmWanMbusD1 41 }

hmWanMbusD1VIF12		OBJECT-TYPE
			SYNTAX	INTEGER
			MAX-ACCESS	read-only
			STATUS	current
			::= { hmWanMbusD1 42 }

hmWanMbusD1Value12		OBJECT-TYPE
			SYNTAX	INTEGER
			MAX-ACCESS	read-only
			STATUS	current
			::= { hmWanMbusD1 43 }

hmWanMbusD1VIF13		OBJECT-TYPE
			SYNTAX	INTEGER
			MAX-ACCESS	read-only
			STATUS	current
			::= { hmWanMbusD1 44 }

hmWanMbusD1Value13		OBJECT-TYPE
			SYNTAX	INTEGER
			MAX-ACCESS	read-only
			STATUS	current
			::= { hmWanMbusD1 45 }

hmWanMbusD1VIF14		OBJECT-TYPE
			SYNTAX	INTEGER
			MAX-ACCESS	read-only
			STATUS	current
			::= { hmWanMbusD1 46 }

hmWanMbusD1Value14		OBJECT-TYPE
			SYNTAX	INTEGER
			MAX-ACCESS	read-only
			STATUS	current
			::= { hmWanMbusD1 47 }

hmWanMbusD1VIF15		OBJECT-TYPE
			SYNTAX	INTEGER
			MAX-ACCESS	read-only
			STATUS	current
			::= { hmWanMbusD1 48 }

hmWanMbusD1Value15		OBJECT-TYPE
			SYNTAX	INTEGER
			MAX-ACCESS	read-only
			STATUS	current
			::= { hmWanMbusD1 49 }

hmWanMbusD1VIF16		OBJECT-TYPE
			SYNTAX	INTEGER
			MAX-ACCESS	read-only
			STATUS	current
			::= { hmWanMbusD1 50 }

hmWanMbusD1Value16		OBJECT-TYPE
			SYNTAX	INTEGER
			MAX-ACCESS	read-only
			STATUS	current
			::= { hmWanMbusD1 51 }

hmWanMbusD1VIF17		OBJECT-TYPE
			SYNTAX	INTEGER
			MAX-ACCESS	read-only
			STATUS	current
			::= { hmWanMbusD1 52 }

hmWanMbusD1Value17		OBJECT-TYPE
			SYNTAX	INTEGER
			MAX-ACCESS	read-only
			STATUS	current
			::= { hmWanMbusD1 53 }

hmWanMbusD1VIF18		OBJECT-TYPE
			SYNTAX	INTEGER
			MAX-ACCESS	read-only
			STATUS	current
			::= { hmWanMbusD1 54 }

hmWanMbusD1Value18		OBJECT-TYPE
			SYNTAX	INTEGER
			MAX-ACCESS	read-only
			STATUS	current
			::= { hmWanMbusD1 55 }

hmWanMbusD1VIF19		OBJECT-TYPE
			SYNTAX	INTEGER
			MAX-ACCESS	read-only
			STATUS	current
			::= { hmWanMbusD1 56 }

hmWanMbusD1Value19		OBJECT-TYPE
			SYNTAX	INTEGER
			MAX-ACCESS	read-only
			STATUS	current
			::= { hmWanMbusD1 57 }

hmWanMbusD1VIF1A		OBJECT-TYPE
			SYNTAX	INTEGER
			MAX-ACCESS	read-only
			STATUS	current
			::= { hmWanMbusD1 58 }

hmWanMbusD1Value1A		OBJECT-TYPE
			SYNTAX	INTEGER
			MAX-ACCESS	read-only
			STATUS	current
			::= { hmWanMbusD1 59 }

hmWanMbusD1VIF1B		OBJECT-TYPE
			SYNTAX	INTEGER
			MAX-ACCESS	read-only
			STATUS	current
			::= { hmWanMbusD1 60 }

hmWanMbusD1Value1B		OBJECT-TYPE
			SYNTAX	INTEGER
			MAX-ACCESS	read-only
			STATUS	current
			::= { hmWanMbusD1 61 }

hmWanMbusD1VIF1C		OBJECT-TYPE
			SYNTAX	INTEGER
			MAX-ACCESS	read-only
			STATUS	current
			::= { hmWanMbusD1 62 }

hmWanMbusD1Value1C		OBJECT-TYPE
			SYNTAX	INTEGER
			MAX-ACCESS	read-only
			STATUS	current
			::= { hmWanMbusD1 63 }

hmWanMbusD1VIF1D		OBJECT-TYPE
			SYNTAX	INTEGER
			MAX-ACCESS	read-only
			STATUS	current
			::= { hmWanMbusD1 64 }

hmWanMbusD1Value1D		OBJECT-TYPE
			SYNTAX	INTEGER
			MAX-ACCESS	read-only
			STATUS	current
			::= { hmWanMbusD1 65 }

hmWanMbusD1VIF1E		OBJECT-TYPE
			SYNTAX	INTEGER
			MAX-ACCESS	read-only
			STATUS	current
			::= { hmWanMbusD1 66 }

hmWanMbusD1Value1E		OBJECT-TYPE
			SYNTAX	INTEGER
			MAX-ACCESS	read-only
			STATUS	current
			::= { hmWanMbusD1 67 }

hmWanMbusD1VIF1F		OBJECT-TYPE
			SYNTAX	INTEGER
			MAX-ACCESS	read-only
			STATUS	current
			::= { hmWanMbusD1 68 }

hmWanMbusD1Value1F		OBJECT-TYPE
			SYNTAX	INTEGER
			MAX-ACCESS	read-only
			STATUS	current
			::= { hmWanMbusD1 69 }

hmWanMbusD1VIF20		OBJECT-TYPE
			SYNTAX	INTEGER
			MAX-ACCESS	read-only
			STATUS	current
			::= { hmWanMbusD1 70 }

hmWanMbusD1Value20		OBJECT-TYPE
			SYNTAX	INTEGER
			MAX-ACCESS	read-only
			STATUS	current
			::= { hmWanMbusD1 71 }

hmWanMbusD1VIF21		OBJECT-TYPE
			SYNTAX	INTEGER
			MAX-ACCESS	read-only
			STATUS	current
			::= { hmWanMbusD1 72 }

hmWanMbusD1Value21		OBJECT-TYPE
			SYNTAX	INTEGER
			MAX-ACCESS	read-only
			STATUS	current
			::= { hmWanMbusD1 73 }

hmWanMbusD1VIF22		OBJECT-TYPE
			SYNTAX	INTEGER
			MAX-ACCESS	read-only
			STATUS	current
			::= { hmWanMbusD1 74 }

hmWanMbusD1Value22		OBJECT-TYPE
			SYNTAX	INTEGER
			MAX-ACCESS	read-only
			STATUS	current
			::= { hmWanMbusD1 75 }

hmWanMbusD1VIF23		OBJECT-TYPE
			SYNTAX	INTEGER
			MAX-ACCESS	read-only
			STATUS	current
			::= { hmWanMbusD1 76 }

hmWanMbusD1Value23		OBJECT-TYPE
			SYNTAX	INTEGER
			MAX-ACCESS	read-only
			STATUS	current
			::= { hmWanMbusD1 77 }

hmWanMbusD1VIF24		OBJECT-TYPE
			SYNTAX	INTEGER
			MAX-ACCESS	read-only
			STATUS	current
			::= { hmWanMbusD1 78 }

hmWanMbusD1Value24		OBJECT-TYPE
			SYNTAX	INTEGER
			MAX-ACCESS	read-only
			STATUS	current
			::= { hmWanMbusD1 79 }

hmWanMbusD1VIF25		OBJECT-TYPE
			SYNTAX	INTEGER
			MAX-ACCESS	read-only
			STATUS	current
			::= { hmWanMbusD1 80 }

hmWanMbusD1Value25		OBJECT-TYPE
			SYNTAX	INTEGER
			MAX-ACCESS	read-only
			STATUS	current
			::= { hmWanMbusD1 81 }

hmWanMbusD1VIF26		OBJECT-TYPE
			SYNTAX	INTEGER
			MAX-ACCESS	read-only
			STATUS	current
			::= { hmWanMbusD1 82 }

hmWanMbusD1Value26		OBJECT-TYPE
			SYNTAX	INTEGER
			MAX-ACCESS	read-only
			STATUS	current
			::= { hmWanMbusD1 83 }

hmWanMbusD1VIF27		OBJECT-TYPE
			SYNTAX	INTEGER
			MAX-ACCESS	read-only
			STATUS	current
			::= { hmWanMbusD1 84 }

hmWanMbusD1Value27		OBJECT-TYPE
			SYNTAX	INTEGER
			MAX-ACCESS	read-only
			STATUS	current
			::= { hmWanMbusD1 85 }

hmWanMbusD1VIF28		OBJECT-TYPE
			SYNTAX	INTEGER
			MAX-ACCESS	read-only
			STATUS	current
			::= { hmWanMbusD1 86 }

hmWanMbusD1Value28		OBJECT-TYPE
			SYNTAX	INTEGER
			MAX-ACCESS	read-only
			STATUS	current
			::= { hmWanMbusD1 87 }

hmWanMbusD1VIF29		OBJECT-TYPE
			SYNTAX	INTEGER
			MAX-ACCESS	read-only
			STATUS	current
			::= { hmWanMbusD1 88 }

hmWanMbusD1Value29		OBJECT-TYPE
			SYNTAX	INTEGER
			MAX-ACCESS	read-only
			STATUS	current
			::= { hmWanMbusD1 89 }

hmWanMbusD1VIF2A		OBJECT-TYPE
			SYNTAX	INTEGER
			MAX-ACCESS	read-only
			STATUS	current
			::= { hmWanMbusD1 90 }

hmWanMbusD1Value2A		OBJECT-TYPE
			SYNTAX	INTEGER
			MAX-ACCESS	read-only
			STATUS	current
			::= { hmWanMbusD1 91 }

hmWanMbusD1VIF2B		OBJECT-TYPE
			SYNTAX	INTEGER
			MAX-ACCESS	read-only
			STATUS	current
			::= { hmWanMbusD1 92 }

hmWanMbusD1Value2B		OBJECT-TYPE
			SYNTAX	INTEGER
			MAX-ACCESS	read-only
			STATUS	current
			::= { hmWanMbusD1 93 }

hmWanMbusD1VIF2C		OBJECT-TYPE
			SYNTAX	INTEGER
			MAX-ACCESS	read-only
			STATUS	current
			::= { hmWanMbusD1 94 }

hmWanMbusD1Value2C		OBJECT-TYPE
			SYNTAX	INTEGER
			MAX-ACCESS	read-only
			STATUS	current
			::= { hmWanMbusD1 95 }

hmWanMbusD1VIF2D		OBJECT-TYPE
			SYNTAX	INTEGER
			MAX-ACCESS	read-only
			STATUS	current
			::= { hmWanMbusD1 96 }

hmWanMbusD1Value2D		OBJECT-TYPE
			SYNTAX	INTEGER
			MAX-ACCESS	read-only
			STATUS	current
			::= { hmWanMbusD1 97 }

hmWanMbusD1VIF2E		OBJECT-TYPE
			SYNTAX	INTEGER
			MAX-ACCESS	read-only
			STATUS	current
			::= { hmWanMbusD1 98 }

hmWanMbusD1Value2E		OBJECT-TYPE
			SYNTAX	INTEGER
			MAX-ACCESS	read-only
			STATUS	current
			::= { hmWanMbusD1 99 }

hmWanMbusD1VIF2F		OBJECT-TYPE
			SYNTAX	INTEGER
			MAX-ACCESS	read-only
			STATUS	current
			::= { hmWanMbusD1 100 }

hmWanMbusD1Value2F		OBJECT-TYPE
			SYNTAX	INTEGER
			MAX-ACCESS	read-only
			STATUS	current
			::= { hmWanMbusD1 101 }

hmWanMbusD2			OBJECT IDENTIFIER ::= { hmWanMbus 210 }

hmWanMbusD2IdNumber		OBJECT-TYPE
			SYNTAX	Gauge32
			MAX-ACCESS	read-only
			STATUS	current
			::= { hmWanMbusD2 1 }

hmWanMbusD2Manufacturer	OBJECT-TYPE
			SYNTAX	Gauge32
			MAX-ACCESS	read-only
			STATUS	current
			::= { hmWanMbusD2 2 }

hmWanMbusD2Version		OBJECT-TYPE
			SYNTAX	Gauge32
			MAX-ACCESS	read-only
			STATUS	current
			::= { hmWanMbusD2 3 }

hmWanMbusD2Medium		OBJECT-TYPE
			SYNTAX	Gauge32
			MAX-ACCESS	read-only
			STATUS	current
			::= { hmWanMbusD2 4 }

hmWanMbusD2Status		OBJECT-TYPE
			SYNTAX	Gauge32
			MAX-ACCESS	read-only
			STATUS	current
			::= { hmWanMbusD2 5 }

hmWanMbusD2VIF00		OBJECT-TYPE
			SYNTAX	INTEGER
			MAX-ACCESS	read-only
			STATUS	current
			::= { hmWanMbusD2 6 }

hmWanMbusD2Value00		OBJECT-TYPE
			SYNTAX	INTEGER
			MAX-ACCESS	read-only
			STATUS	current
			::= { hmWanMbusD2 7 }

hmWanMbusD2VIF01		OBJECT-TYPE
			SYNTAX	INTEGER
			MAX-ACCESS	read-only
			STATUS	current
			::= { hmWanMbusD2 8 }

hmWanMbusD2Value01		OBJECT-TYPE
			SYNTAX	INTEGER
			MAX-ACCESS	read-only
			STATUS	current
			::= { hmWanMbusD2 9 }

hmWanMbusD2VIF02		OBJECT-TYPE
			SYNTAX	INTEGER
			MAX-ACCESS	read-only
			STATUS	current
			::= { hmWanMbusD2 10 }

hmWanMbusD2Value02		OBJECT-TYPE
			SYNTAX	INTEGER
			MAX-ACCESS	read-only
			STATUS	current
			::= { hmWanMbusD2 11 }

hmWanMbusD2VIF03		OBJECT-TYPE
			SYNTAX	INTEGER
			MAX-ACCESS	read-only
			STATUS	current
			::= { hmWanMbusD2 12 }

hmWanMbusD2Value03		OBJECT-TYPE
			SYNTAX	INTEGER
			MAX-ACCESS	read-only
			STATUS	current
			::= { hmWanMbusD2 13 }

hmWanMbusD2VIF04		OBJECT-TYPE
			SYNTAX	INTEGER
			MAX-ACCESS	read-only
			STATUS	current
			::= { hmWanMbusD2 14 }

hmWanMbusD2Value04		OBJECT-TYPE
			SYNTAX	INTEGER
			MAX-ACCESS	read-only
			STATUS	current
			::= { hmWanMbusD2 15 }

hmWanMbusD2VIF05		OBJECT-TYPE
			SYNTAX	INTEGER
			MAX-ACCESS	read-only
			STATUS	current
			::= { hmWanMbusD2 16 }

hmWanMbusD2Value05		OBJECT-TYPE
			SYNTAX	INTEGER
			MAX-ACCESS	read-only
			STATUS	current
			::= { hmWanMbusD2 17 }

hmWanMbusD2VIF06		OBJECT-TYPE
			SYNTAX	INTEGER
			MAX-ACCESS	read-only
			STATUS	current
			::= { hmWanMbusD2 18 }

hmWanMbusD2Value06		OBJECT-TYPE
			SYNTAX	INTEGER
			MAX-ACCESS	read-only
			STATUS	current
			::= { hmWanMbusD2 19 }

hmWanMbusD2VIF07		OBJECT-TYPE
			SYNTAX	INTEGER
			MAX-ACCESS	read-only
			STATUS	current
			::= { hmWanMbusD2 20 }

hmWanMbusD2Value07		OBJECT-TYPE
			SYNTAX	INTEGER
			MAX-ACCESS	read-only
			STATUS	current
			::= { hmWanMbusD2 21 }

hmWanMbusD2VIF08		OBJECT-TYPE
			SYNTAX	INTEGER
			MAX-ACCESS	read-only
			STATUS	current
			::= { hmWanMbusD2 22 }

hmWanMbusD2Value08		OBJECT-TYPE
			SYNTAX	INTEGER
			MAX-ACCESS	read-only
			STATUS	current
			::= { hmWanMbusD2 23 }

hmWanMbusD2VIF09		OBJECT-TYPE
			SYNTAX	INTEGER
			MAX-ACCESS	read-only
			STATUS	current
			::= { hmWanMbusD2 24 }

hmWanMbusD2Value09		OBJECT-TYPE
			SYNTAX	INTEGER
			MAX-ACCESS	read-only
			STATUS	current
			::= { hmWanMbusD2 25 }

hmWanMbusD2VIF0A		OBJECT-TYPE
			SYNTAX	INTEGER
			MAX-ACCESS	read-only
			STATUS	current
			::= { hmWanMbusD2 26 }

hmWanMbusD2Value0A		OBJECT-TYPE
			SYNTAX	INTEGER
			MAX-ACCESS	read-only
			STATUS	current
			::= { hmWanMbusD2 27 }

hmWanMbusD2VIF0B		OBJECT-TYPE
			SYNTAX	INTEGER
			MAX-ACCESS	read-only
			STATUS	current
			::= { hmWanMbusD2 28 }

hmWanMbusD2Value0B		OBJECT-TYPE
			SYNTAX	INTEGER
			MAX-ACCESS	read-only
			STATUS	current
			::= { hmWanMbusD2 29 }

hmWanMbusD2VIF0C		OBJECT-TYPE
			SYNTAX	INTEGER
			MAX-ACCESS	read-only
			STATUS	current
			::= { hmWanMbusD2 30 }

hmWanMbusD2Value0C		OBJECT-TYPE
			SYNTAX	INTEGER
			MAX-ACCESS	read-only
			STATUS	current
			::= { hmWanMbusD2 31 }

hmWanMbusD2VIF0D		OBJECT-TYPE
			SYNTAX	INTEGER
			MAX-ACCESS	read-only
			STATUS	current
			::= { hmWanMbusD2 32 }

hmWanMbusD2Value0D		OBJECT-TYPE
			SYNTAX	INTEGER
			MAX-ACCESS	read-only
			STATUS	current
			::= { hmWanMbusD2 33 }

hmWanMbusD2VIF0E		OBJECT-TYPE
			SYNTAX	INTEGER
			MAX-ACCESS	read-only
			STATUS	current
			::= { hmWanMbusD2 34 }

hmWanMbusD2Value0E		OBJECT-TYPE
			SYNTAX	INTEGER
			MAX-ACCESS	read-only
			STATUS	current
			::= { hmWanMbusD2 35 }

hmWanMbusD2VIF0F		OBJECT-TYPE
			SYNTAX	INTEGER
			MAX-ACCESS	read-only
			STATUS	current
			::= { hmWanMbusD2 36 }

hmWanMbusD2Value0F		OBJECT-TYPE
			SYNTAX	INTEGER
			MAX-ACCESS	read-only
			STATUS	current
			::= { hmWanMbusD2 37 }

hmWanMbusD2VIF10		OBJECT-TYPE
			SYNTAX	INTEGER
			MAX-ACCESS	read-only
			STATUS	current
			::= { hmWanMbusD2 38 }

hmWanMbusD2Value10		OBJECT-TYPE
			SYNTAX	INTEGER
			MAX-ACCESS	read-only
			STATUS	current
			::= { hmWanMbusD2 39 }

hmWanMbusD2VIF11		OBJECT-TYPE
			SYNTAX	INTEGER
			MAX-ACCESS	read-only
			STATUS	current
			::= { hmWanMbusD2 40 }

hmWanMbusD2Value11		OBJECT-TYPE
			SYNTAX	INTEGER
			MAX-ACCESS	read-only
			STATUS	current
			::= { hmWanMbusD2 41 }

hmWanMbusD2VIF12		OBJECT-TYPE
			SYNTAX	INTEGER
			MAX-ACCESS	read-only
			STATUS	current
			::= { hmWanMbusD2 42 }

hmWanMbusD2Value12		OBJECT-TYPE
			SYNTAX	INTEGER
			MAX-ACCESS	read-only
			STATUS	current
			::= { hmWanMbusD2 43 }

hmWanMbusD2VIF13		OBJECT-TYPE
			SYNTAX	INTEGER
			MAX-ACCESS	read-only
			STATUS	current
			::= { hmWanMbusD2 44 }

hmWanMbusD2Value13		OBJECT-TYPE
			SYNTAX	INTEGER
			MAX-ACCESS	read-only
			STATUS	current
			::= { hmWanMbusD2 45 }

hmWanMbusD2VIF14		OBJECT-TYPE
			SYNTAX	INTEGER
			MAX-ACCESS	read-only
			STATUS	current
			::= { hmWanMbusD2 46 }

hmWanMbusD2Value14		OBJECT-TYPE
			SYNTAX	INTEGER
			MAX-ACCESS	read-only
			STATUS	current
			::= { hmWanMbusD2 47 }

hmWanMbusD2VIF15		OBJECT-TYPE
			SYNTAX	INTEGER
			MAX-ACCESS	read-only
			STATUS	current
			::= { hmWanMbusD2 48 }

hmWanMbusD2Value15		OBJECT-TYPE
			SYNTAX	INTEGER
			MAX-ACCESS	read-only
			STATUS	current
			::= { hmWanMbusD2 49 }

hmWanMbusD2VIF16		OBJECT-TYPE
			SYNTAX	INTEGER
			MAX-ACCESS	read-only
			STATUS	current
			::= { hmWanMbusD2 50 }

hmWanMbusD2Value16		OBJECT-TYPE
			SYNTAX	INTEGER
			MAX-ACCESS	read-only
			STATUS	current
			::= { hmWanMbusD2 51 }

hmWanMbusD2VIF17		OBJECT-TYPE
			SYNTAX	INTEGER
			MAX-ACCESS	read-only
			STATUS	current
			::= { hmWanMbusD2 52 }

hmWanMbusD2Value17		OBJECT-TYPE
			SYNTAX	INTEGER
			MAX-ACCESS	read-only
			STATUS	current
			::= { hmWanMbusD2 53 }

hmWanMbusD2VIF18		OBJECT-TYPE
			SYNTAX	INTEGER
			MAX-ACCESS	read-only
			STATUS	current
			::= { hmWanMbusD2 54 }

hmWanMbusD2Value18		OBJECT-TYPE
			SYNTAX	INTEGER
			MAX-ACCESS	read-only
			STATUS	current
			::= { hmWanMbusD2 55 }

hmWanMbusD2VIF19		OBJECT-TYPE
			SYNTAX	INTEGER
			MAX-ACCESS	read-only
			STATUS	current
			::= { hmWanMbusD2 56 }

hmWanMbusD2Value19		OBJECT-TYPE
			SYNTAX	INTEGER
			MAX-ACCESS	read-only
			STATUS	current
			::= { hmWanMbusD2 57 }

hmWanMbusD2VIF1A		OBJECT-TYPE
			SYNTAX	INTEGER
			MAX-ACCESS	read-only
			STATUS	current
			::= { hmWanMbusD2 58 }

hmWanMbusD2Value1A		OBJECT-TYPE
			SYNTAX	INTEGER
			MAX-ACCESS	read-only
			STATUS	current
			::= { hmWanMbusD2 59 }

hmWanMbusD2VIF1B		OBJECT-TYPE
			SYNTAX	INTEGER
			MAX-ACCESS	read-only
			STATUS	current
			::= { hmWanMbusD2 60 }

hmWanMbusD2Value1B		OBJECT-TYPE
			SYNTAX	INTEGER
			MAX-ACCESS	read-only
			STATUS	current
			::= { hmWanMbusD2 61 }

hmWanMbusD2VIF1C		OBJECT-TYPE
			SYNTAX	INTEGER
			MAX-ACCESS	read-only
			STATUS	current
			::= { hmWanMbusD2 62 }

hmWanMbusD2Value1C		OBJECT-TYPE
			SYNTAX	INTEGER
			MAX-ACCESS	read-only
			STATUS	current
			::= { hmWanMbusD2 63 }

hmWanMbusD2VIF1D		OBJECT-TYPE
			SYNTAX	INTEGER
			MAX-ACCESS	read-only
			STATUS	current
			::= { hmWanMbusD2 64 }

hmWanMbusD2Value1D		OBJECT-TYPE
			SYNTAX	INTEGER
			MAX-ACCESS	read-only
			STATUS	current
			::= { hmWanMbusD2 65 }

hmWanMbusD2VIF1E		OBJECT-TYPE
			SYNTAX	INTEGER
			MAX-ACCESS	read-only
			STATUS	current
			::= { hmWanMbusD2 66 }

hmWanMbusD2Value1E		OBJECT-TYPE
			SYNTAX	INTEGER
			MAX-ACCESS	read-only
			STATUS	current
			::= { hmWanMbusD2 67 }

hmWanMbusD2VIF1F		OBJECT-TYPE
			SYNTAX	INTEGER
			MAX-ACCESS	read-only
			STATUS	current
			::= { hmWanMbusD2 68 }

hmWanMbusD2Value1F		OBJECT-TYPE
			SYNTAX	INTEGER
			MAX-ACCESS	read-only
			STATUS	current
			::= { hmWanMbusD2 69 }

hmWanMbusD2VIF20		OBJECT-TYPE
			SYNTAX	INTEGER
			MAX-ACCESS	read-only
			STATUS	current
			::= { hmWanMbusD2 70 }

hmWanMbusD2Value20		OBJECT-TYPE
			SYNTAX	INTEGER
			MAX-ACCESS	read-only
			STATUS	current
			::= { hmWanMbusD2 71 }

hmWanMbusD2VIF21		OBJECT-TYPE
			SYNTAX	INTEGER
			MAX-ACCESS	read-only
			STATUS	current
			::= { hmWanMbusD2 72 }

hmWanMbusD2Value21		OBJECT-TYPE
			SYNTAX	INTEGER
			MAX-ACCESS	read-only
			STATUS	current
			::= { hmWanMbusD2 73 }

hmWanMbusD2VIF22		OBJECT-TYPE
			SYNTAX	INTEGER
			MAX-ACCESS	read-only
			STATUS	current
			::= { hmWanMbusD2 74 }

hmWanMbusD2Value22		OBJECT-TYPE
			SYNTAX	INTEGER
			MAX-ACCESS	read-only
			STATUS	current
			::= { hmWanMbusD2 75 }

hmWanMbusD2VIF23		OBJECT-TYPE
			SYNTAX	INTEGER
			MAX-ACCESS	read-only
			STATUS	current
			::= { hmWanMbusD2 76 }

hmWanMbusD2Value23		OBJECT-TYPE
			SYNTAX	INTEGER
			MAX-ACCESS	read-only
			STATUS	current
			::= { hmWanMbusD2 77 }

hmWanMbusD2VIF24		OBJECT-TYPE
			SYNTAX	INTEGER
			MAX-ACCESS	read-only
			STATUS	current
			::= { hmWanMbusD2 78 }

hmWanMbusD2Value24		OBJECT-TYPE
			SYNTAX	INTEGER
			MAX-ACCESS	read-only
			STATUS	current
			::= { hmWanMbusD2 79 }

hmWanMbusD2VIF25		OBJECT-TYPE
			SYNTAX	INTEGER
			MAX-ACCESS	read-only
			STATUS	current
			::= { hmWanMbusD2 80 }

hmWanMbusD2Value25		OBJECT-TYPE
			SYNTAX	INTEGER
			MAX-ACCESS	read-only
			STATUS	current
			::= { hmWanMbusD2 81 }

hmWanMbusD2VIF26		OBJECT-TYPE
			SYNTAX	INTEGER
			MAX-ACCESS	read-only
			STATUS	current
			::= { hmWanMbusD2 82 }

hmWanMbusD2Value26		OBJECT-TYPE
			SYNTAX	INTEGER
			MAX-ACCESS	read-only
			STATUS	current
			::= { hmWanMbusD2 83 }

hmWanMbusD2VIF27		OBJECT-TYPE
			SYNTAX	INTEGER
			MAX-ACCESS	read-only
			STATUS	current
			::= { hmWanMbusD2 84 }

hmWanMbusD2Value27		OBJECT-TYPE
			SYNTAX	INTEGER
			MAX-ACCESS	read-only
			STATUS	current
			::= { hmWanMbusD2 85 }

hmWanMbusD2VIF28		OBJECT-TYPE
			SYNTAX	INTEGER
			MAX-ACCESS	read-only
			STATUS	current
			::= { hmWanMbusD2 86 }

hmWanMbusD2Value28		OBJECT-TYPE
			SYNTAX	INTEGER
			MAX-ACCESS	read-only
			STATUS	current
			::= { hmWanMbusD2 87 }

hmWanMbusD2VIF29		OBJECT-TYPE
			SYNTAX	INTEGER
			MAX-ACCESS	read-only
			STATUS	current
			::= { hmWanMbusD2 88 }

hmWanMbusD2Value29		OBJECT-TYPE
			SYNTAX	INTEGER
			MAX-ACCESS	read-only
			STATUS	current
			::= { hmWanMbusD2 89 }

hmWanMbusD2VIF2A		OBJECT-TYPE
			SYNTAX	INTEGER
			MAX-ACCESS	read-only
			STATUS	current
			::= { hmWanMbusD2 90 }

hmWanMbusD2Value2A		OBJECT-TYPE
			SYNTAX	INTEGER
			MAX-ACCESS	read-only
			STATUS	current
			::= { hmWanMbusD2 91 }

hmWanMbusD2VIF2B		OBJECT-TYPE
			SYNTAX	INTEGER
			MAX-ACCESS	read-only
			STATUS	current
			::= { hmWanMbusD2 92 }

hmWanMbusD2Value2B		OBJECT-TYPE
			SYNTAX	INTEGER
			MAX-ACCESS	read-only
			STATUS	current
			::= { hmWanMbusD2 93 }

hmWanMbusD2VIF2C		OBJECT-TYPE
			SYNTAX	INTEGER
			MAX-ACCESS	read-only
			STATUS	current
			::= { hmWanMbusD2 94 }

hmWanMbusD2Value2C		OBJECT-TYPE
			SYNTAX	INTEGER
			MAX-ACCESS	read-only
			STATUS	current
			::= { hmWanMbusD2 95 }

hmWanMbusD2VIF2D		OBJECT-TYPE
			SYNTAX	INTEGER
			MAX-ACCESS	read-only
			STATUS	current
			::= { hmWanMbusD2 96 }

hmWanMbusD2Value2D		OBJECT-TYPE
			SYNTAX	INTEGER
			MAX-ACCESS	read-only
			STATUS	current
			::= { hmWanMbusD2 97 }

hmWanMbusD2VIF2E		OBJECT-TYPE
			SYNTAX	INTEGER
			MAX-ACCESS	read-only
			STATUS	current
			::= { hmWanMbusD2 98 }

hmWanMbusD2Value2E		OBJECT-TYPE
			SYNTAX	INTEGER
			MAX-ACCESS	read-only
			STATUS	current
			::= { hmWanMbusD2 99 }

hmWanMbusD2VIF2F		OBJECT-TYPE
			SYNTAX	INTEGER
			MAX-ACCESS	read-only
			STATUS	current
			::= { hmWanMbusD2 100 }

hmWanMbusD2Value2F		OBJECT-TYPE
			SYNTAX	INTEGER
			MAX-ACCESS	read-only
			STATUS	current
			::= { hmWanMbusD2 101 }

hmWanMbusD3			OBJECT IDENTIFIER ::= { hmWanMbus 211 }

hmWanMbusD3IdNumber		OBJECT-TYPE
			SYNTAX	Gauge32
			MAX-ACCESS	read-only
			STATUS	current
			::= { hmWanMbusD3 1 }

hmWanMbusD3Manufacturer	OBJECT-TYPE
			SYNTAX	Gauge32
			MAX-ACCESS	read-only
			STATUS	current
			::= { hmWanMbusD3 2 }

hmWanMbusD3Version		OBJECT-TYPE
			SYNTAX	Gauge32
			MAX-ACCESS	read-only
			STATUS	current
			::= { hmWanMbusD3 3 }

hmWanMbusD3Medium		OBJECT-TYPE
			SYNTAX	Gauge32
			MAX-ACCESS	read-only
			STATUS	current
			::= { hmWanMbusD3 4 }

hmWanMbusD3Status		OBJECT-TYPE
			SYNTAX	Gauge32
			MAX-ACCESS	read-only
			STATUS	current
			::= { hmWanMbusD3 5 }

hmWanMbusD3VIF00		OBJECT-TYPE
			SYNTAX	INTEGER
			MAX-ACCESS	read-only
			STATUS	current
			::= { hmWanMbusD3 6 }

hmWanMbusD3Value00		OBJECT-TYPE
			SYNTAX	INTEGER
			MAX-ACCESS	read-only
			STATUS	current
			::= { hmWanMbusD3 7 }

hmWanMbusD3VIF01		OBJECT-TYPE
			SYNTAX	INTEGER
			MAX-ACCESS	read-only
			STATUS	current
			::= { hmWanMbusD3 8 }

hmWanMbusD3Value01		OBJECT-TYPE
			SYNTAX	INTEGER
			MAX-ACCESS	read-only
			STATUS	current
			::= { hmWanMbusD3 9 }

hmWanMbusD3VIF02		OBJECT-TYPE
			SYNTAX	INTEGER
			MAX-ACCESS	read-only
			STATUS	current
			::= { hmWanMbusD3 10 }

hmWanMbusD3Value02		OBJECT-TYPE
			SYNTAX	INTEGER
			MAX-ACCESS	read-only
			STATUS	current
			::= { hmWanMbusD3 11 }

hmWanMbusD3VIF03		OBJECT-TYPE
			SYNTAX	INTEGER
			MAX-ACCESS	read-only
			STATUS	current
			::= { hmWanMbusD3 12 }

hmWanMbusD3Value03		OBJECT-TYPE
			SYNTAX	INTEGER
			MAX-ACCESS	read-only
			STATUS	current
			::= { hmWanMbusD3 13 }

hmWanMbusD3VIF04		OBJECT-TYPE
			SYNTAX	INTEGER
			MAX-ACCESS	read-only
			STATUS	current
			::= { hmWanMbusD3 14 }

hmWanMbusD3Value04		OBJECT-TYPE
			SYNTAX	INTEGER
			MAX-ACCESS	read-only
			STATUS	current
			::= { hmWanMbusD3 15 }

hmWanMbusD3VIF05		OBJECT-TYPE
			SYNTAX	INTEGER
			MAX-ACCESS	read-only
			STATUS	current
			::= { hmWanMbusD3 16 }

hmWanMbusD3Value05		OBJECT-TYPE
			SYNTAX	INTEGER
			MAX-ACCESS	read-only
			STATUS	current
			::= { hmWanMbusD3 17 }

hmWanMbusD3VIF06		OBJECT-TYPE
			SYNTAX	INTEGER
			MAX-ACCESS	read-only
			STATUS	current
			::= { hmWanMbusD3 18 }

hmWanMbusD3Value06		OBJECT-TYPE
			SYNTAX	INTEGER
			MAX-ACCESS	read-only
			STATUS	current
			::= { hmWanMbusD3 19 }

hmWanMbusD3VIF07		OBJECT-TYPE
			SYNTAX	INTEGER
			MAX-ACCESS	read-only
			STATUS	current
			::= { hmWanMbusD3 20 }

hmWanMbusD3Value07		OBJECT-TYPE
			SYNTAX	INTEGER
			MAX-ACCESS	read-only
			STATUS	current
			::= { hmWanMbusD3 21 }

hmWanMbusD3VIF08		OBJECT-TYPE
			SYNTAX	INTEGER
			MAX-ACCESS	read-only
			STATUS	current
			::= { hmWanMbusD3 22 }

hmWanMbusD3Value08		OBJECT-TYPE
			SYNTAX	INTEGER
			MAX-ACCESS	read-only
			STATUS	current
			::= { hmWanMbusD3 23 }

hmWanMbusD3VIF09		OBJECT-TYPE
			SYNTAX	INTEGER
			MAX-ACCESS	read-only
			STATUS	current
			::= { hmWanMbusD3 24 }

hmWanMbusD3Value09		OBJECT-TYPE
			SYNTAX	INTEGER
			MAX-ACCESS	read-only
			STATUS	current
			::= { hmWanMbusD3 25 }

hmWanMbusD3VIF0A		OBJECT-TYPE
			SYNTAX	INTEGER
			MAX-ACCESS	read-only
			STATUS	current
			::= { hmWanMbusD3 26 }

hmWanMbusD3Value0A		OBJECT-TYPE
			SYNTAX	INTEGER
			MAX-ACCESS	read-only
			STATUS	current
			::= { hmWanMbusD3 27 }

hmWanMbusD3VIF0B		OBJECT-TYPE
			SYNTAX	INTEGER
			MAX-ACCESS	read-only
			STATUS	current
			::= { hmWanMbusD3 28 }

hmWanMbusD3Value0B		OBJECT-TYPE
			SYNTAX	INTEGER
			MAX-ACCESS	read-only
			STATUS	current
			::= { hmWanMbusD3 29 }

hmWanMbusD3VIF0C		OBJECT-TYPE
			SYNTAX	INTEGER
			MAX-ACCESS	read-only
			STATUS	current
			::= { hmWanMbusD3 30 }

hmWanMbusD3Value0C		OBJECT-TYPE
			SYNTAX	INTEGER
			MAX-ACCESS	read-only
			STATUS	current
			::= { hmWanMbusD3 31 }

hmWanMbusD3VIF0D		OBJECT-TYPE
			SYNTAX	INTEGER
			MAX-ACCESS	read-only
			STATUS	current
			::= { hmWanMbusD3 32 }

hmWanMbusD3Value0D		OBJECT-TYPE
			SYNTAX	INTEGER
			MAX-ACCESS	read-only
			STATUS	current
			::= { hmWanMbusD3 33 }

hmWanMbusD3VIF0E		OBJECT-TYPE
			SYNTAX	INTEGER
			MAX-ACCESS	read-only
			STATUS	current
			::= { hmWanMbusD3 34 }

hmWanMbusD3Value0E		OBJECT-TYPE
			SYNTAX	INTEGER
			MAX-ACCESS	read-only
			STATUS	current
			::= { hmWanMbusD3 35 }

hmWanMbusD3VIF0F		OBJECT-TYPE
			SYNTAX	INTEGER
			MAX-ACCESS	read-only
			STATUS	current
			::= { hmWanMbusD3 36 }

hmWanMbusD3Value0F		OBJECT-TYPE
			SYNTAX	INTEGER
			MAX-ACCESS	read-only
			STATUS	current
			::= { hmWanMbusD3 37 }

hmWanMbusD3VIF10		OBJECT-TYPE
			SYNTAX	INTEGER
			MAX-ACCESS	read-only
			STATUS	current
			::= { hmWanMbusD3 38 }

hmWanMbusD3Value10		OBJECT-TYPE
			SYNTAX	INTEGER
			MAX-ACCESS	read-only
			STATUS	current
			::= { hmWanMbusD3 39 }

hmWanMbusD3VIF11		OBJECT-TYPE
			SYNTAX	INTEGER
			MAX-ACCESS	read-only
			STATUS	current
			::= { hmWanMbusD3 40 }

hmWanMbusD3Value11		OBJECT-TYPE
			SYNTAX	INTEGER
			MAX-ACCESS	read-only
			STATUS	current
			::= { hmWanMbusD3 41 }

hmWanMbusD3VIF12		OBJECT-TYPE
			SYNTAX	INTEGER
			MAX-ACCESS	read-only
			STATUS	current
			::= { hmWanMbusD3 42 }

hmWanMbusD3Value12		OBJECT-TYPE
			SYNTAX	INTEGER
			MAX-ACCESS	read-only
			STATUS	current
			::= { hmWanMbusD3 43 }

hmWanMbusD3VIF13		OBJECT-TYPE
			SYNTAX	INTEGER
			MAX-ACCESS	read-only
			STATUS	current
			::= { hmWanMbusD3 44 }

hmWanMbusD3Value13		OBJECT-TYPE
			SYNTAX	INTEGER
			MAX-ACCESS	read-only
			STATUS	current
			::= { hmWanMbusD3 45 }

hmWanMbusD3VIF14		OBJECT-TYPE
			SYNTAX	INTEGER
			MAX-ACCESS	read-only
			STATUS	current
			::= { hmWanMbusD3 46 }

hmWanMbusD3Value14		OBJECT-TYPE
			SYNTAX	INTEGER
			MAX-ACCESS	read-only
			STATUS	current
			::= { hmWanMbusD3 47 }

hmWanMbusD3VIF15		OBJECT-TYPE
			SYNTAX	INTEGER
			MAX-ACCESS	read-only
			STATUS	current
			::= { hmWanMbusD3 48 }

hmWanMbusD3Value15		OBJECT-TYPE
			SYNTAX	INTEGER
			MAX-ACCESS	read-only
			STATUS	current
			::= { hmWanMbusD3 49 }

hmWanMbusD3VIF16		OBJECT-TYPE
			SYNTAX	INTEGER
			MAX-ACCESS	read-only
			STATUS	current
			::= { hmWanMbusD3 50 }

hmWanMbusD3Value16		OBJECT-TYPE
			SYNTAX	INTEGER
			MAX-ACCESS	read-only
			STATUS	current
			::= { hmWanMbusD3 51 }

hmWanMbusD3VIF17		OBJECT-TYPE
			SYNTAX	INTEGER
			MAX-ACCESS	read-only
			STATUS	current
			::= { hmWanMbusD3 52 }

hmWanMbusD3Value17		OBJECT-TYPE
			SYNTAX	INTEGER
			MAX-ACCESS	read-only
			STATUS	current
			::= { hmWanMbusD3 53 }

hmWanMbusD3VIF18		OBJECT-TYPE
			SYNTAX	INTEGER
			MAX-ACCESS	read-only
			STATUS	current
			::= { hmWanMbusD3 54 }

hmWanMbusD3Value18		OBJECT-TYPE
			SYNTAX	INTEGER
			MAX-ACCESS	read-only
			STATUS	current
			::= { hmWanMbusD3 55 }

hmWanMbusD3VIF19		OBJECT-TYPE
			SYNTAX	INTEGER
			MAX-ACCESS	read-only
			STATUS	current
			::= { hmWanMbusD3 56 }

hmWanMbusD3Value19		OBJECT-TYPE
			SYNTAX	INTEGER
			MAX-ACCESS	read-only
			STATUS	current
			::= { hmWanMbusD3 57 }

hmWanMbusD3VIF1A		OBJECT-TYPE
			SYNTAX	INTEGER
			MAX-ACCESS	read-only
			STATUS	current
			::= { hmWanMbusD3 58 }

hmWanMbusD3Value1A		OBJECT-TYPE
			SYNTAX	INTEGER
			MAX-ACCESS	read-only
			STATUS	current
			::= { hmWanMbusD3 59 }

hmWanMbusD3VIF1B		OBJECT-TYPE
			SYNTAX	INTEGER
			MAX-ACCESS	read-only
			STATUS	current
			::= { hmWanMbusD3 60 }

hmWanMbusD3Value1B		OBJECT-TYPE
			SYNTAX	INTEGER
			MAX-ACCESS	read-only
			STATUS	current
			::= { hmWanMbusD3 61 }

hmWanMbusD3VIF1C		OBJECT-TYPE
			SYNTAX	INTEGER
			MAX-ACCESS	read-only
			STATUS	current
			::= { hmWanMbusD3 62 }

hmWanMbusD3Value1C		OBJECT-TYPE
			SYNTAX	INTEGER
			MAX-ACCESS	read-only
			STATUS	current
			::= { hmWanMbusD3 63 }

hmWanMbusD3VIF1D		OBJECT-TYPE
			SYNTAX	INTEGER
			MAX-ACCESS	read-only
			STATUS	current
			::= { hmWanMbusD3 64 }

hmWanMbusD3Value1D		OBJECT-TYPE
			SYNTAX	INTEGER
			MAX-ACCESS	read-only
			STATUS	current
			::= { hmWanMbusD3 65 }

hmWanMbusD3VIF1E		OBJECT-TYPE
			SYNTAX	INTEGER
			MAX-ACCESS	read-only
			STATUS	current
			::= { hmWanMbusD3 66 }

hmWanMbusD3Value1E		OBJECT-TYPE
			SYNTAX	INTEGER
			MAX-ACCESS	read-only
			STATUS	current
			::= { hmWanMbusD3 67 }

hmWanMbusD3VIF1F		OBJECT-TYPE
			SYNTAX	INTEGER
			MAX-ACCESS	read-only
			STATUS	current
			::= { hmWanMbusD3 68 }

hmWanMbusD3Value1F		OBJECT-TYPE
			SYNTAX	INTEGER
			MAX-ACCESS	read-only
			STATUS	current
			::= { hmWanMbusD3 69 }

hmWanMbusD3VIF20		OBJECT-TYPE
			SYNTAX	INTEGER
			MAX-ACCESS	read-only
			STATUS	current
			::= { hmWanMbusD3 70 }

hmWanMbusD3Value20		OBJECT-TYPE
			SYNTAX	INTEGER
			MAX-ACCESS	read-only
			STATUS	current
			::= { hmWanMbusD3 71 }

hmWanMbusD3VIF21		OBJECT-TYPE
			SYNTAX	INTEGER
			MAX-ACCESS	read-only
			STATUS	current
			::= { hmWanMbusD3 72 }

hmWanMbusD3Value21		OBJECT-TYPE
			SYNTAX	INTEGER
			MAX-ACCESS	read-only
			STATUS	current
			::= { hmWanMbusD3 73 }

hmWanMbusD3VIF22		OBJECT-TYPE
			SYNTAX	INTEGER
			MAX-ACCESS	read-only
			STATUS	current
			::= { hmWanMbusD3 74 }

hmWanMbusD3Value22		OBJECT-TYPE
			SYNTAX	INTEGER
			MAX-ACCESS	read-only
			STATUS	current
			::= { hmWanMbusD3 75 }

hmWanMbusD3VIF23		OBJECT-TYPE
			SYNTAX	INTEGER
			MAX-ACCESS	read-only
			STATUS	current
			::= { hmWanMbusD3 76 }

hmWanMbusD3Value23		OBJECT-TYPE
			SYNTAX	INTEGER
			MAX-ACCESS	read-only
			STATUS	current
			::= { hmWanMbusD3 77 }

hmWanMbusD3VIF24		OBJECT-TYPE
			SYNTAX	INTEGER
			MAX-ACCESS	read-only
			STATUS	current
			::= { hmWanMbusD3 78 }

hmWanMbusD3Value24		OBJECT-TYPE
			SYNTAX	INTEGER
			MAX-ACCESS	read-only
			STATUS	current
			::= { hmWanMbusD3 79 }

hmWanMbusD3VIF25		OBJECT-TYPE
			SYNTAX	INTEGER
			MAX-ACCESS	read-only
			STATUS	current
			::= { hmWanMbusD3 80 }

hmWanMbusD3Value25		OBJECT-TYPE
			SYNTAX	INTEGER
			MAX-ACCESS	read-only
			STATUS	current
			::= { hmWanMbusD3 81 }

hmWanMbusD3VIF26		OBJECT-TYPE
			SYNTAX	INTEGER
			MAX-ACCESS	read-only
			STATUS	current
			::= { hmWanMbusD3 82 }

hmWanMbusD3Value26		OBJECT-TYPE
			SYNTAX	INTEGER
			MAX-ACCESS	read-only
			STATUS	current
			::= { hmWanMbusD3 83 }

hmWanMbusD3VIF27		OBJECT-TYPE
			SYNTAX	INTEGER
			MAX-ACCESS	read-only
			STATUS	current
			::= { hmWanMbusD3 84 }

hmWanMbusD3Value27		OBJECT-TYPE
			SYNTAX	INTEGER
			MAX-ACCESS	read-only
			STATUS	current
			::= { hmWanMbusD3 85 }

hmWanMbusD3VIF28		OBJECT-TYPE
			SYNTAX	INTEGER
			MAX-ACCESS	read-only
			STATUS	current
			::= { hmWanMbusD3 86 }

hmWanMbusD3Value28		OBJECT-TYPE
			SYNTAX	INTEGER
			MAX-ACCESS	read-only
			STATUS	current
			::= { hmWanMbusD3 87 }

hmWanMbusD3VIF29		OBJECT-TYPE
			SYNTAX	INTEGER
			MAX-ACCESS	read-only
			STATUS	current
			::= { hmWanMbusD3 88 }

hmWanMbusD3Value29		OBJECT-TYPE
			SYNTAX	INTEGER
			MAX-ACCESS	read-only
			STATUS	current
			::= { hmWanMbusD3 89 }

hmWanMbusD3VIF2A		OBJECT-TYPE
			SYNTAX	INTEGER
			MAX-ACCESS	read-only
			STATUS	current
			::= { hmWanMbusD3 90 }

hmWanMbusD3Value2A		OBJECT-TYPE
			SYNTAX	INTEGER
			MAX-ACCESS	read-only
			STATUS	current
			::= { hmWanMbusD3 91 }

hmWanMbusD3VIF2B		OBJECT-TYPE
			SYNTAX	INTEGER
			MAX-ACCESS	read-only
			STATUS	current
			::= { hmWanMbusD3 92 }

hmWanMbusD3Value2B		OBJECT-TYPE
			SYNTAX	INTEGER
			MAX-ACCESS	read-only
			STATUS	current
			::= { hmWanMbusD3 93 }

hmWanMbusD3VIF2C		OBJECT-TYPE
			SYNTAX	INTEGER
			MAX-ACCESS	read-only
			STATUS	current
			::= { hmWanMbusD3 94 }

hmWanMbusD3Value2C		OBJECT-TYPE
			SYNTAX	INTEGER
			MAX-ACCESS	read-only
			STATUS	current
			::= { hmWanMbusD3 95 }

hmWanMbusD3VIF2D		OBJECT-TYPE
			SYNTAX	INTEGER
			MAX-ACCESS	read-only
			STATUS	current
			::= { hmWanMbusD3 96 }

hmWanMbusD3Value2D		OBJECT-TYPE
			SYNTAX	INTEGER
			MAX-ACCESS	read-only
			STATUS	current
			::= { hmWanMbusD3 97 }

hmWanMbusD3VIF2E		OBJECT-TYPE
			SYNTAX	INTEGER
			MAX-ACCESS	read-only
			STATUS	current
			::= { hmWanMbusD3 98 }

hmWanMbusD3Value2E		OBJECT-TYPE
			SYNTAX	INTEGER
			MAX-ACCESS	read-only
			STATUS	current
			::= { hmWanMbusD3 99 }

hmWanMbusD3VIF2F		OBJECT-TYPE
			SYNTAX	INTEGER
			MAX-ACCESS	read-only
			STATUS	current
			::= { hmWanMbusD3 100 }

hmWanMbusD3Value2F		OBJECT-TYPE
			SYNTAX	INTEGER
			MAX-ACCESS	read-only
			STATUS	current
			::= { hmWanMbusD3 101 }

hmWanMbusD4			OBJECT IDENTIFIER ::= { hmWanMbus 212 }

hmWanMbusD4IdNumber		OBJECT-TYPE
			SYNTAX	Gauge32
			MAX-ACCESS	read-only
			STATUS	current
			::= { hmWanMbusD4 1 }

hmWanMbusD4Manufacturer	OBJECT-TYPE
			SYNTAX	Gauge32
			MAX-ACCESS	read-only
			STATUS	current
			::= { hmWanMbusD4 2 }

hmWanMbusD4Version		OBJECT-TYPE
			SYNTAX	Gauge32
			MAX-ACCESS	read-only
			STATUS	current
			::= { hmWanMbusD4 3 }

hmWanMbusD4Medium		OBJECT-TYPE
			SYNTAX	Gauge32
			MAX-ACCESS	read-only
			STATUS	current
			::= { hmWanMbusD4 4 }

hmWanMbusD4Status		OBJECT-TYPE
			SYNTAX	Gauge32
			MAX-ACCESS	read-only
			STATUS	current
			::= { hmWanMbusD4 5 }

hmWanMbusD4VIF00		OBJECT-TYPE
			SYNTAX	INTEGER
			MAX-ACCESS	read-only
			STATUS	current
			::= { hmWanMbusD4 6 }

hmWanMbusD4Value00		OBJECT-TYPE
			SYNTAX	INTEGER
			MAX-ACCESS	read-only
			STATUS	current
			::= { hmWanMbusD4 7 }

hmWanMbusD4VIF01		OBJECT-TYPE
			SYNTAX	INTEGER
			MAX-ACCESS	read-only
			STATUS	current
			::= { hmWanMbusD4 8 }

hmWanMbusD4Value01		OBJECT-TYPE
			SYNTAX	INTEGER
			MAX-ACCESS	read-only
			STATUS	current
			::= { hmWanMbusD4 9 }

hmWanMbusD4VIF02		OBJECT-TYPE
			SYNTAX	INTEGER
			MAX-ACCESS	read-only
			STATUS	current
			::= { hmWanMbusD4 10 }

hmWanMbusD4Value02		OBJECT-TYPE
			SYNTAX	INTEGER
			MAX-ACCESS	read-only
			STATUS	current
			::= { hmWanMbusD4 11 }

hmWanMbusD4VIF03		OBJECT-TYPE
			SYNTAX	INTEGER
			MAX-ACCESS	read-only
			STATUS	current
			::= { hmWanMbusD4 12 }

hmWanMbusD4Value03		OBJECT-TYPE
			SYNTAX	INTEGER
			MAX-ACCESS	read-only
			STATUS	current
			::= { hmWanMbusD4 13 }

hmWanMbusD4VIF04		OBJECT-TYPE
			SYNTAX	INTEGER
			MAX-ACCESS	read-only
			STATUS	current
			::= { hmWanMbusD4 14 }

hmWanMbusD4Value04		OBJECT-TYPE
			SYNTAX	INTEGER
			MAX-ACCESS	read-only
			STATUS	current
			::= { hmWanMbusD4 15 }

hmWanMbusD4VIF05		OBJECT-TYPE
			SYNTAX	INTEGER
			MAX-ACCESS	read-only
			STATUS	current
			::= { hmWanMbusD4 16 }

hmWanMbusD4Value05		OBJECT-TYPE
			SYNTAX	INTEGER
			MAX-ACCESS	read-only
			STATUS	current
			::= { hmWanMbusD4 17 }

hmWanMbusD4VIF06		OBJECT-TYPE
			SYNTAX	INTEGER
			MAX-ACCESS	read-only
			STATUS	current
			::= { hmWanMbusD4 18 }

hmWanMbusD4Value06		OBJECT-TYPE
			SYNTAX	INTEGER
			MAX-ACCESS	read-only
			STATUS	current
			::= { hmWanMbusD4 19 }

hmWanMbusD4VIF07		OBJECT-TYPE
			SYNTAX	INTEGER
			MAX-ACCESS	read-only
			STATUS	current
			::= { hmWanMbusD4 20 }

hmWanMbusD4Value07		OBJECT-TYPE
			SYNTAX	INTEGER
			MAX-ACCESS	read-only
			STATUS	current
			::= { hmWanMbusD4 21 }

hmWanMbusD4VIF08		OBJECT-TYPE
			SYNTAX	INTEGER
			MAX-ACCESS	read-only
			STATUS	current
			::= { hmWanMbusD4 22 }

hmWanMbusD4Value08		OBJECT-TYPE
			SYNTAX	INTEGER
			MAX-ACCESS	read-only
			STATUS	current
			::= { hmWanMbusD4 23 }

hmWanMbusD4VIF09		OBJECT-TYPE
			SYNTAX	INTEGER
			MAX-ACCESS	read-only
			STATUS	current
			::= { hmWanMbusD4 24 }

hmWanMbusD4Value09		OBJECT-TYPE
			SYNTAX	INTEGER
			MAX-ACCESS	read-only
			STATUS	current
			::= { hmWanMbusD4 25 }

hmWanMbusD4VIF0A		OBJECT-TYPE
			SYNTAX	INTEGER
			MAX-ACCESS	read-only
			STATUS	current
			::= { hmWanMbusD4 26 }

hmWanMbusD4Value0A		OBJECT-TYPE
			SYNTAX	INTEGER
			MAX-ACCESS	read-only
			STATUS	current
			::= { hmWanMbusD4 27 }

hmWanMbusD4VIF0B		OBJECT-TYPE
			SYNTAX	INTEGER
			MAX-ACCESS	read-only
			STATUS	current
			::= { hmWanMbusD4 28 }

hmWanMbusD4Value0B		OBJECT-TYPE
			SYNTAX	INTEGER
			MAX-ACCESS	read-only
			STATUS	current
			::= { hmWanMbusD4 29 }

hmWanMbusD4VIF0C		OBJECT-TYPE
			SYNTAX	INTEGER
			MAX-ACCESS	read-only
			STATUS	current
			::= { hmWanMbusD4 30 }

hmWanMbusD4Value0C		OBJECT-TYPE
			SYNTAX	INTEGER
			MAX-ACCESS	read-only
			STATUS	current
			::= { hmWanMbusD4 31 }

hmWanMbusD4VIF0D		OBJECT-TYPE
			SYNTAX	INTEGER
			MAX-ACCESS	read-only
			STATUS	current
			::= { hmWanMbusD4 32 }

hmWanMbusD4Value0D		OBJECT-TYPE
			SYNTAX	INTEGER
			MAX-ACCESS	read-only
			STATUS	current
			::= { hmWanMbusD4 33 }

hmWanMbusD4VIF0E		OBJECT-TYPE
			SYNTAX	INTEGER
			MAX-ACCESS	read-only
			STATUS	current
			::= { hmWanMbusD4 34 }

hmWanMbusD4Value0E		OBJECT-TYPE
			SYNTAX	INTEGER
			MAX-ACCESS	read-only
			STATUS	current
			::= { hmWanMbusD4 35 }

hmWanMbusD4VIF0F		OBJECT-TYPE
			SYNTAX	INTEGER
			MAX-ACCESS	read-only
			STATUS	current
			::= { hmWanMbusD4 36 }

hmWanMbusD4Value0F		OBJECT-TYPE
			SYNTAX	INTEGER
			MAX-ACCESS	read-only
			STATUS	current
			::= { hmWanMbusD4 37 }

hmWanMbusD4VIF10		OBJECT-TYPE
			SYNTAX	INTEGER
			MAX-ACCESS	read-only
			STATUS	current
			::= { hmWanMbusD4 38 }

hmWanMbusD4Value10		OBJECT-TYPE
			SYNTAX	INTEGER
			MAX-ACCESS	read-only
			STATUS	current
			::= { hmWanMbusD4 39 }

hmWanMbusD4VIF11		OBJECT-TYPE
			SYNTAX	INTEGER
			MAX-ACCESS	read-only
			STATUS	current
			::= { hmWanMbusD4 40 }

hmWanMbusD4Value11		OBJECT-TYPE
			SYNTAX	INTEGER
			MAX-ACCESS	read-only
			STATUS	current
			::= { hmWanMbusD4 41 }

hmWanMbusD4VIF12		OBJECT-TYPE
			SYNTAX	INTEGER
			MAX-ACCESS	read-only
			STATUS	current
			::= { hmWanMbusD4 42 }

hmWanMbusD4Value12		OBJECT-TYPE
			SYNTAX	INTEGER
			MAX-ACCESS	read-only
			STATUS	current
			::= { hmWanMbusD4 43 }

hmWanMbusD4VIF13		OBJECT-TYPE
			SYNTAX	INTEGER
			MAX-ACCESS	read-only
			STATUS	current
			::= { hmWanMbusD4 44 }

hmWanMbusD4Value13		OBJECT-TYPE
			SYNTAX	INTEGER
			MAX-ACCESS	read-only
			STATUS	current
			::= { hmWanMbusD4 45 }

hmWanMbusD4VIF14		OBJECT-TYPE
			SYNTAX	INTEGER
			MAX-ACCESS	read-only
			STATUS	current
			::= { hmWanMbusD4 46 }

hmWanMbusD4Value14		OBJECT-TYPE
			SYNTAX	INTEGER
			MAX-ACCESS	read-only
			STATUS	current
			::= { hmWanMbusD4 47 }

hmWanMbusD4VIF15		OBJECT-TYPE
			SYNTAX	INTEGER
			MAX-ACCESS	read-only
			STATUS	current
			::= { hmWanMbusD4 48 }

hmWanMbusD4Value15		OBJECT-TYPE
			SYNTAX	INTEGER
			MAX-ACCESS	read-only
			STATUS	current
			::= { hmWanMbusD4 49 }

hmWanMbusD4VIF16		OBJECT-TYPE
			SYNTAX	INTEGER
			MAX-ACCESS	read-only
			STATUS	current
			::= { hmWanMbusD4 50 }

hmWanMbusD4Value16		OBJECT-TYPE
			SYNTAX	INTEGER
			MAX-ACCESS	read-only
			STATUS	current
			::= { hmWanMbusD4 51 }

hmWanMbusD4VIF17		OBJECT-TYPE
			SYNTAX	INTEGER
			MAX-ACCESS	read-only
			STATUS	current
			::= { hmWanMbusD4 52 }

hmWanMbusD4Value17		OBJECT-TYPE
			SYNTAX	INTEGER
			MAX-ACCESS	read-only
			STATUS	current
			::= { hmWanMbusD4 53 }

hmWanMbusD4VIF18		OBJECT-TYPE
			SYNTAX	INTEGER
			MAX-ACCESS	read-only
			STATUS	current
			::= { hmWanMbusD4 54 }

hmWanMbusD4Value18		OBJECT-TYPE
			SYNTAX	INTEGER
			MAX-ACCESS	read-only
			STATUS	current
			::= { hmWanMbusD4 55 }

hmWanMbusD4VIF19		OBJECT-TYPE
			SYNTAX	INTEGER
			MAX-ACCESS	read-only
			STATUS	current
			::= { hmWanMbusD4 56 }

hmWanMbusD4Value19		OBJECT-TYPE
			SYNTAX	INTEGER
			MAX-ACCESS	read-only
			STATUS	current
			::= { hmWanMbusD4 57 }

hmWanMbusD4VIF1A		OBJECT-TYPE
			SYNTAX	INTEGER
			MAX-ACCESS	read-only
			STATUS	current
			::= { hmWanMbusD4 58 }

hmWanMbusD4Value1A		OBJECT-TYPE
			SYNTAX	INTEGER
			MAX-ACCESS	read-only
			STATUS	current
			::= { hmWanMbusD4 59 }

hmWanMbusD4VIF1B		OBJECT-TYPE
			SYNTAX	INTEGER
			MAX-ACCESS	read-only
			STATUS	current
			::= { hmWanMbusD4 60 }

hmWanMbusD4Value1B		OBJECT-TYPE
			SYNTAX	INTEGER
			MAX-ACCESS	read-only
			STATUS	current
			::= { hmWanMbusD4 61 }

hmWanMbusD4VIF1C		OBJECT-TYPE
			SYNTAX	INTEGER
			MAX-ACCESS	read-only
			STATUS	current
			::= { hmWanMbusD4 62 }

hmWanMbusD4Value1C		OBJECT-TYPE
			SYNTAX	INTEGER
			MAX-ACCESS	read-only
			STATUS	current
			::= { hmWanMbusD4 63 }

hmWanMbusD4VIF1D		OBJECT-TYPE
			SYNTAX	INTEGER
			MAX-ACCESS	read-only
			STATUS	current
			::= { hmWanMbusD4 64 }

hmWanMbusD4Value1D		OBJECT-TYPE
			SYNTAX	INTEGER
			MAX-ACCESS	read-only
			STATUS	current
			::= { hmWanMbusD4 65 }

hmWanMbusD4VIF1E		OBJECT-TYPE
			SYNTAX	INTEGER
			MAX-ACCESS	read-only
			STATUS	current
			::= { hmWanMbusD4 66 }

hmWanMbusD4Value1E		OBJECT-TYPE
			SYNTAX	INTEGER
			MAX-ACCESS	read-only
			STATUS	current
			::= { hmWanMbusD4 67 }

hmWanMbusD4VIF1F		OBJECT-TYPE
			SYNTAX	INTEGER
			MAX-ACCESS	read-only
			STATUS	current
			::= { hmWanMbusD4 68 }

hmWanMbusD4Value1F		OBJECT-TYPE
			SYNTAX	INTEGER
			MAX-ACCESS	read-only
			STATUS	current
			::= { hmWanMbusD4 69 }

hmWanMbusD4VIF20		OBJECT-TYPE
			SYNTAX	INTEGER
			MAX-ACCESS	read-only
			STATUS	current
			::= { hmWanMbusD4 70 }

hmWanMbusD4Value20		OBJECT-TYPE
			SYNTAX	INTEGER
			MAX-ACCESS	read-only
			STATUS	current
			::= { hmWanMbusD4 71 }

hmWanMbusD4VIF21		OBJECT-TYPE
			SYNTAX	INTEGER
			MAX-ACCESS	read-only
			STATUS	current
			::= { hmWanMbusD4 72 }

hmWanMbusD4Value21		OBJECT-TYPE
			SYNTAX	INTEGER
			MAX-ACCESS	read-only
			STATUS	current
			::= { hmWanMbusD4 73 }

hmWanMbusD4VIF22		OBJECT-TYPE
			SYNTAX	INTEGER
			MAX-ACCESS	read-only
			STATUS	current
			::= { hmWanMbusD4 74 }

hmWanMbusD4Value22		OBJECT-TYPE
			SYNTAX	INTEGER
			MAX-ACCESS	read-only
			STATUS	current
			::= { hmWanMbusD4 75 }

hmWanMbusD4VIF23		OBJECT-TYPE
			SYNTAX	INTEGER
			MAX-ACCESS	read-only
			STATUS	current
			::= { hmWanMbusD4 76 }

hmWanMbusD4Value23		OBJECT-TYPE
			SYNTAX	INTEGER
			MAX-ACCESS	read-only
			STATUS	current
			::= { hmWanMbusD4 77 }

hmWanMbusD4VIF24		OBJECT-TYPE
			SYNTAX	INTEGER
			MAX-ACCESS	read-only
			STATUS	current
			::= { hmWanMbusD4 78 }

hmWanMbusD4Value24		OBJECT-TYPE
			SYNTAX	INTEGER
			MAX-ACCESS	read-only
			STATUS	current
			::= { hmWanMbusD4 79 }

hmWanMbusD4VIF25		OBJECT-TYPE
			SYNTAX	INTEGER
			MAX-ACCESS	read-only
			STATUS	current
			::= { hmWanMbusD4 80 }

hmWanMbusD4Value25		OBJECT-TYPE
			SYNTAX	INTEGER
			MAX-ACCESS	read-only
			STATUS	current
			::= { hmWanMbusD4 81 }

hmWanMbusD4VIF26		OBJECT-TYPE
			SYNTAX	INTEGER
			MAX-ACCESS	read-only
			STATUS	current
			::= { hmWanMbusD4 82 }

hmWanMbusD4Value26		OBJECT-TYPE
			SYNTAX	INTEGER
			MAX-ACCESS	read-only
			STATUS	current
			::= { hmWanMbusD4 83 }

hmWanMbusD4VIF27		OBJECT-TYPE
			SYNTAX	INTEGER
			MAX-ACCESS	read-only
			STATUS	current
			::= { hmWanMbusD4 84 }

hmWanMbusD4Value27		OBJECT-TYPE
			SYNTAX	INTEGER
			MAX-ACCESS	read-only
			STATUS	current
			::= { hmWanMbusD4 85 }

hmWanMbusD4VIF28		OBJECT-TYPE
			SYNTAX	INTEGER
			MAX-ACCESS	read-only
			STATUS	current
			::= { hmWanMbusD4 86 }

hmWanMbusD4Value28		OBJECT-TYPE
			SYNTAX	INTEGER
			MAX-ACCESS	read-only
			STATUS	current
			::= { hmWanMbusD4 87 }

hmWanMbusD4VIF29		OBJECT-TYPE
			SYNTAX	INTEGER
			MAX-ACCESS	read-only
			STATUS	current
			::= { hmWanMbusD4 88 }

hmWanMbusD4Value29		OBJECT-TYPE
			SYNTAX	INTEGER
			MAX-ACCESS	read-only
			STATUS	current
			::= { hmWanMbusD4 89 }

hmWanMbusD4VIF2A		OBJECT-TYPE
			SYNTAX	INTEGER
			MAX-ACCESS	read-only
			STATUS	current
			::= { hmWanMbusD4 90 }

hmWanMbusD4Value2A		OBJECT-TYPE
			SYNTAX	INTEGER
			MAX-ACCESS	read-only
			STATUS	current
			::= { hmWanMbusD4 91 }

hmWanMbusD4VIF2B		OBJECT-TYPE
			SYNTAX	INTEGER
			MAX-ACCESS	read-only
			STATUS	current
			::= { hmWanMbusD4 92 }

hmWanMbusD4Value2B		OBJECT-TYPE
			SYNTAX	INTEGER
			MAX-ACCESS	read-only
			STATUS	current
			::= { hmWanMbusD4 93 }

hmWanMbusD4VIF2C		OBJECT-TYPE
			SYNTAX	INTEGER
			MAX-ACCESS	read-only
			STATUS	current
			::= { hmWanMbusD4 94 }

hmWanMbusD4Value2C		OBJECT-TYPE
			SYNTAX	INTEGER
			MAX-ACCESS	read-only
			STATUS	current
			::= { hmWanMbusD4 95 }

hmWanMbusD4VIF2D		OBJECT-TYPE
			SYNTAX	INTEGER
			MAX-ACCESS	read-only
			STATUS	current
			::= { hmWanMbusD4 96 }

hmWanMbusD4Value2D		OBJECT-TYPE
			SYNTAX	INTEGER
			MAX-ACCESS	read-only
			STATUS	current
			::= { hmWanMbusD4 97 }

hmWanMbusD4VIF2E		OBJECT-TYPE
			SYNTAX	INTEGER
			MAX-ACCESS	read-only
			STATUS	current
			::= { hmWanMbusD4 98 }

hmWanMbusD4Value2E		OBJECT-TYPE
			SYNTAX	INTEGER
			MAX-ACCESS	read-only
			STATUS	current
			::= { hmWanMbusD4 99 }

hmWanMbusD4VIF2F		OBJECT-TYPE
			SYNTAX	INTEGER
			MAX-ACCESS	read-only
			STATUS	current
			::= { hmWanMbusD4 100 }

hmWanMbusD4Value2F		OBJECT-TYPE
			SYNTAX	INTEGER
			MAX-ACCESS	read-only
			STATUS	current
			::= { hmWanMbusD4 101 }

hmWanMbusD5			OBJECT IDENTIFIER ::= { hmWanMbus 213 }

hmWanMbusD5IdNumber		OBJECT-TYPE
			SYNTAX	Gauge32
			MAX-ACCESS	read-only
			STATUS	current
			::= { hmWanMbusD5 1 }

hmWanMbusD5Manufacturer	OBJECT-TYPE
			SYNTAX	Gauge32
			MAX-ACCESS	read-only
			STATUS	current
			::= { hmWanMbusD5 2 }

hmWanMbusD5Version		OBJECT-TYPE
			SYNTAX	Gauge32
			MAX-ACCESS	read-only
			STATUS	current
			::= { hmWanMbusD5 3 }

hmWanMbusD5Medium		OBJECT-TYPE
			SYNTAX	Gauge32
			MAX-ACCESS	read-only
			STATUS	current
			::= { hmWanMbusD5 4 }

hmWanMbusD5Status		OBJECT-TYPE
			SYNTAX	Gauge32
			MAX-ACCESS	read-only
			STATUS	current
			::= { hmWanMbusD5 5 }

hmWanMbusD5VIF00		OBJECT-TYPE
			SYNTAX	INTEGER
			MAX-ACCESS	read-only
			STATUS	current
			::= { hmWanMbusD5 6 }

hmWanMbusD5Value00		OBJECT-TYPE
			SYNTAX	INTEGER
			MAX-ACCESS	read-only
			STATUS	current
			::= { hmWanMbusD5 7 }

hmWanMbusD5VIF01		OBJECT-TYPE
			SYNTAX	INTEGER
			MAX-ACCESS	read-only
			STATUS	current
			::= { hmWanMbusD5 8 }

hmWanMbusD5Value01		OBJECT-TYPE
			SYNTAX	INTEGER
			MAX-ACCESS	read-only
			STATUS	current
			::= { hmWanMbusD5 9 }

hmWanMbusD5VIF02		OBJECT-TYPE
			SYNTAX	INTEGER
			MAX-ACCESS	read-only
			STATUS	current
			::= { hmWanMbusD5 10 }

hmWanMbusD5Value02		OBJECT-TYPE
			SYNTAX	INTEGER
			MAX-ACCESS	read-only
			STATUS	current
			::= { hmWanMbusD5 11 }

hmWanMbusD5VIF03		OBJECT-TYPE
			SYNTAX	INTEGER
			MAX-ACCESS	read-only
			STATUS	current
			::= { hmWanMbusD5 12 }

hmWanMbusD5Value03		OBJECT-TYPE
			SYNTAX	INTEGER
			MAX-ACCESS	read-only
			STATUS	current
			::= { hmWanMbusD5 13 }

hmWanMbusD5VIF04		OBJECT-TYPE
			SYNTAX	INTEGER
			MAX-ACCESS	read-only
			STATUS	current
			::= { hmWanMbusD5 14 }

hmWanMbusD5Value04		OBJECT-TYPE
			SYNTAX	INTEGER
			MAX-ACCESS	read-only
			STATUS	current
			::= { hmWanMbusD5 15 }

hmWanMbusD5VIF05		OBJECT-TYPE
			SYNTAX	INTEGER
			MAX-ACCESS	read-only
			STATUS	current
			::= { hmWanMbusD5 16 }

hmWanMbusD5Value05		OBJECT-TYPE
			SYNTAX	INTEGER
			MAX-ACCESS	read-only
			STATUS	current
			::= { hmWanMbusD5 17 }

hmWanMbusD5VIF06		OBJECT-TYPE
			SYNTAX	INTEGER
			MAX-ACCESS	read-only
			STATUS	current
			::= { hmWanMbusD5 18 }

hmWanMbusD5Value06		OBJECT-TYPE
			SYNTAX	INTEGER
			MAX-ACCESS	read-only
			STATUS	current
			::= { hmWanMbusD5 19 }

hmWanMbusD5VIF07		OBJECT-TYPE
			SYNTAX	INTEGER
			MAX-ACCESS	read-only
			STATUS	current
			::= { hmWanMbusD5 20 }

hmWanMbusD5Value07		OBJECT-TYPE
			SYNTAX	INTEGER
			MAX-ACCESS	read-only
			STATUS	current
			::= { hmWanMbusD5 21 }

hmWanMbusD5VIF08		OBJECT-TYPE
			SYNTAX	INTEGER
			MAX-ACCESS	read-only
			STATUS	current
			::= { hmWanMbusD5 22 }

hmWanMbusD5Value08		OBJECT-TYPE
			SYNTAX	INTEGER
			MAX-ACCESS	read-only
			STATUS	current
			::= { hmWanMbusD5 23 }

hmWanMbusD5VIF09		OBJECT-TYPE
			SYNTAX	INTEGER
			MAX-ACCESS	read-only
			STATUS	current
			::= { hmWanMbusD5 24 }

hmWanMbusD5Value09		OBJECT-TYPE
			SYNTAX	INTEGER
			MAX-ACCESS	read-only
			STATUS	current
			::= { hmWanMbusD5 25 }

hmWanMbusD5VIF0A		OBJECT-TYPE
			SYNTAX	INTEGER
			MAX-ACCESS	read-only
			STATUS	current
			::= { hmWanMbusD5 26 }

hmWanMbusD5Value0A		OBJECT-TYPE
			SYNTAX	INTEGER
			MAX-ACCESS	read-only
			STATUS	current
			::= { hmWanMbusD5 27 }

hmWanMbusD5VIF0B		OBJECT-TYPE
			SYNTAX	INTEGER
			MAX-ACCESS	read-only
			STATUS	current
			::= { hmWanMbusD5 28 }

hmWanMbusD5Value0B		OBJECT-TYPE
			SYNTAX	INTEGER
			MAX-ACCESS	read-only
			STATUS	current
			::= { hmWanMbusD5 29 }

hmWanMbusD5VIF0C		OBJECT-TYPE
			SYNTAX	INTEGER
			MAX-ACCESS	read-only
			STATUS	current
			::= { hmWanMbusD5 30 }

hmWanMbusD5Value0C		OBJECT-TYPE
			SYNTAX	INTEGER
			MAX-ACCESS	read-only
			STATUS	current
			::= { hmWanMbusD5 31 }

hmWanMbusD5VIF0D		OBJECT-TYPE
			SYNTAX	INTEGER
			MAX-ACCESS	read-only
			STATUS	current
			::= { hmWanMbusD5 32 }

hmWanMbusD5Value0D		OBJECT-TYPE
			SYNTAX	INTEGER
			MAX-ACCESS	read-only
			STATUS	current
			::= { hmWanMbusD5 33 }

hmWanMbusD5VIF0E		OBJECT-TYPE
			SYNTAX	INTEGER
			MAX-ACCESS	read-only
			STATUS	current
			::= { hmWanMbusD5 34 }

hmWanMbusD5Value0E		OBJECT-TYPE
			SYNTAX	INTEGER
			MAX-ACCESS	read-only
			STATUS	current
			::= { hmWanMbusD5 35 }

hmWanMbusD5VIF0F		OBJECT-TYPE
			SYNTAX	INTEGER
			MAX-ACCESS	read-only
			STATUS	current
			::= { hmWanMbusD5 36 }

hmWanMbusD5Value0F		OBJECT-TYPE
			SYNTAX	INTEGER
			MAX-ACCESS	read-only
			STATUS	current
			::= { hmWanMbusD5 37 }

hmWanMbusD5VIF10		OBJECT-TYPE
			SYNTAX	INTEGER
			MAX-ACCESS	read-only
			STATUS	current
			::= { hmWanMbusD5 38 }

hmWanMbusD5Value10		OBJECT-TYPE
			SYNTAX	INTEGER
			MAX-ACCESS	read-only
			STATUS	current
			::= { hmWanMbusD5 39 }

hmWanMbusD5VIF11		OBJECT-TYPE
			SYNTAX	INTEGER
			MAX-ACCESS	read-only
			STATUS	current
			::= { hmWanMbusD5 40 }

hmWanMbusD5Value11		OBJECT-TYPE
			SYNTAX	INTEGER
			MAX-ACCESS	read-only
			STATUS	current
			::= { hmWanMbusD5 41 }

hmWanMbusD5VIF12		OBJECT-TYPE
			SYNTAX	INTEGER
			MAX-ACCESS	read-only
			STATUS	current
			::= { hmWanMbusD5 42 }

hmWanMbusD5Value12		OBJECT-TYPE
			SYNTAX	INTEGER
			MAX-ACCESS	read-only
			STATUS	current
			::= { hmWanMbusD5 43 }

hmWanMbusD5VIF13		OBJECT-TYPE
			SYNTAX	INTEGER
			MAX-ACCESS	read-only
			STATUS	current
			::= { hmWanMbusD5 44 }

hmWanMbusD5Value13		OBJECT-TYPE
			SYNTAX	INTEGER
			MAX-ACCESS	read-only
			STATUS	current
			::= { hmWanMbusD5 45 }

hmWanMbusD5VIF14		OBJECT-TYPE
			SYNTAX	INTEGER
			MAX-ACCESS	read-only
			STATUS	current
			::= { hmWanMbusD5 46 }

hmWanMbusD5Value14		OBJECT-TYPE
			SYNTAX	INTEGER
			MAX-ACCESS	read-only
			STATUS	current
			::= { hmWanMbusD5 47 }

hmWanMbusD5VIF15		OBJECT-TYPE
			SYNTAX	INTEGER
			MAX-ACCESS	read-only
			STATUS	current
			::= { hmWanMbusD5 48 }

hmWanMbusD5Value15		OBJECT-TYPE
			SYNTAX	INTEGER
			MAX-ACCESS	read-only
			STATUS	current
			::= { hmWanMbusD5 49 }

hmWanMbusD5VIF16		OBJECT-TYPE
			SYNTAX	INTEGER
			MAX-ACCESS	read-only
			STATUS	current
			::= { hmWanMbusD5 50 }

hmWanMbusD5Value16		OBJECT-TYPE
			SYNTAX	INTEGER
			MAX-ACCESS	read-only
			STATUS	current
			::= { hmWanMbusD5 51 }

hmWanMbusD5VIF17		OBJECT-TYPE
			SYNTAX	INTEGER
			MAX-ACCESS	read-only
			STATUS	current
			::= { hmWanMbusD5 52 }

hmWanMbusD5Value17		OBJECT-TYPE
			SYNTAX	INTEGER
			MAX-ACCESS	read-only
			STATUS	current
			::= { hmWanMbusD5 53 }

hmWanMbusD5VIF18		OBJECT-TYPE
			SYNTAX	INTEGER
			MAX-ACCESS	read-only
			STATUS	current
			::= { hmWanMbusD5 54 }

hmWanMbusD5Value18		OBJECT-TYPE
			SYNTAX	INTEGER
			MAX-ACCESS	read-only
			STATUS	current
			::= { hmWanMbusD5 55 }

hmWanMbusD5VIF19		OBJECT-TYPE
			SYNTAX	INTEGER
			MAX-ACCESS	read-only
			STATUS	current
			::= { hmWanMbusD5 56 }

hmWanMbusD5Value19		OBJECT-TYPE
			SYNTAX	INTEGER
			MAX-ACCESS	read-only
			STATUS	current
			::= { hmWanMbusD5 57 }

hmWanMbusD5VIF1A		OBJECT-TYPE
			SYNTAX	INTEGER
			MAX-ACCESS	read-only
			STATUS	current
			::= { hmWanMbusD5 58 }

hmWanMbusD5Value1A		OBJECT-TYPE
			SYNTAX	INTEGER
			MAX-ACCESS	read-only
			STATUS	current
			::= { hmWanMbusD5 59 }

hmWanMbusD5VIF1B		OBJECT-TYPE
			SYNTAX	INTEGER
			MAX-ACCESS	read-only
			STATUS	current
			::= { hmWanMbusD5 60 }

hmWanMbusD5Value1B		OBJECT-TYPE
			SYNTAX	INTEGER
			MAX-ACCESS	read-only
			STATUS	current
			::= { hmWanMbusD5 61 }

hmWanMbusD5VIF1C		OBJECT-TYPE
			SYNTAX	INTEGER
			MAX-ACCESS	read-only
			STATUS	current
			::= { hmWanMbusD5 62 }

hmWanMbusD5Value1C		OBJECT-TYPE
			SYNTAX	INTEGER
			MAX-ACCESS	read-only
			STATUS	current
			::= { hmWanMbusD5 63 }

hmWanMbusD5VIF1D		OBJECT-TYPE
			SYNTAX	INTEGER
			MAX-ACCESS	read-only
			STATUS	current
			::= { hmWanMbusD5 64 }

hmWanMbusD5Value1D		OBJECT-TYPE
			SYNTAX	INTEGER
			MAX-ACCESS	read-only
			STATUS	current
			::= { hmWanMbusD5 65 }

hmWanMbusD5VIF1E		OBJECT-TYPE
			SYNTAX	INTEGER
			MAX-ACCESS	read-only
			STATUS	current
			::= { hmWanMbusD5 66 }

hmWanMbusD5Value1E		OBJECT-TYPE
			SYNTAX	INTEGER
			MAX-ACCESS	read-only
			STATUS	current
			::= { hmWanMbusD5 67 }

hmWanMbusD5VIF1F		OBJECT-TYPE
			SYNTAX	INTEGER
			MAX-ACCESS	read-only
			STATUS	current
			::= { hmWanMbusD5 68 }

hmWanMbusD5Value1F		OBJECT-TYPE
			SYNTAX	INTEGER
			MAX-ACCESS	read-only
			STATUS	current
			::= { hmWanMbusD5 69 }

hmWanMbusD5VIF20		OBJECT-TYPE
			SYNTAX	INTEGER
			MAX-ACCESS	read-only
			STATUS	current
			::= { hmWanMbusD5 70 }

hmWanMbusD5Value20		OBJECT-TYPE
			SYNTAX	INTEGER
			MAX-ACCESS	read-only
			STATUS	current
			::= { hmWanMbusD5 71 }

hmWanMbusD5VIF21		OBJECT-TYPE
			SYNTAX	INTEGER
			MAX-ACCESS	read-only
			STATUS	current
			::= { hmWanMbusD5 72 }

hmWanMbusD5Value21		OBJECT-TYPE
			SYNTAX	INTEGER
			MAX-ACCESS	read-only
			STATUS	current
			::= { hmWanMbusD5 73 }

hmWanMbusD5VIF22		OBJECT-TYPE
			SYNTAX	INTEGER
			MAX-ACCESS	read-only
			STATUS	current
			::= { hmWanMbusD5 74 }

hmWanMbusD5Value22		OBJECT-TYPE
			SYNTAX	INTEGER
			MAX-ACCESS	read-only
			STATUS	current
			::= { hmWanMbusD5 75 }

hmWanMbusD5VIF23		OBJECT-TYPE
			SYNTAX	INTEGER
			MAX-ACCESS	read-only
			STATUS	current
			::= { hmWanMbusD5 76 }

hmWanMbusD5Value23		OBJECT-TYPE
			SYNTAX	INTEGER
			MAX-ACCESS	read-only
			STATUS	current
			::= { hmWanMbusD5 77 }

hmWanMbusD5VIF24		OBJECT-TYPE
			SYNTAX	INTEGER
			MAX-ACCESS	read-only
			STATUS	current
			::= { hmWanMbusD5 78 }

hmWanMbusD5Value24		OBJECT-TYPE
			SYNTAX	INTEGER
			MAX-ACCESS	read-only
			STATUS	current
			::= { hmWanMbusD5 79 }

hmWanMbusD5VIF25		OBJECT-TYPE
			SYNTAX	INTEGER
			MAX-ACCESS	read-only
			STATUS	current
			::= { hmWanMbusD5 80 }

hmWanMbusD5Value25		OBJECT-TYPE
			SYNTAX	INTEGER
			MAX-ACCESS	read-only
			STATUS	current
			::= { hmWanMbusD5 81 }

hmWanMbusD5VIF26		OBJECT-TYPE
			SYNTAX	INTEGER
			MAX-ACCESS	read-only
			STATUS	current
			::= { hmWanMbusD5 82 }

hmWanMbusD5Value26		OBJECT-TYPE
			SYNTAX	INTEGER
			MAX-ACCESS	read-only
			STATUS	current
			::= { hmWanMbusD5 83 }

hmWanMbusD5VIF27		OBJECT-TYPE
			SYNTAX	INTEGER
			MAX-ACCESS	read-only
			STATUS	current
			::= { hmWanMbusD5 84 }

hmWanMbusD5Value27		OBJECT-TYPE
			SYNTAX	INTEGER
			MAX-ACCESS	read-only
			STATUS	current
			::= { hmWanMbusD5 85 }

hmWanMbusD5VIF28		OBJECT-TYPE
			SYNTAX	INTEGER
			MAX-ACCESS	read-only
			STATUS	current
			::= { hmWanMbusD5 86 }

hmWanMbusD5Value28		OBJECT-TYPE
			SYNTAX	INTEGER
			MAX-ACCESS	read-only
			STATUS	current
			::= { hmWanMbusD5 87 }

hmWanMbusD5VIF29		OBJECT-TYPE
			SYNTAX	INTEGER
			MAX-ACCESS	read-only
			STATUS	current
			::= { hmWanMbusD5 88 }

hmWanMbusD5Value29		OBJECT-TYPE
			SYNTAX	INTEGER
			MAX-ACCESS	read-only
			STATUS	current
			::= { hmWanMbusD5 89 }

hmWanMbusD5VIF2A		OBJECT-TYPE
			SYNTAX	INTEGER
			MAX-ACCESS	read-only
			STATUS	current
			::= { hmWanMbusD5 90 }

hmWanMbusD5Value2A		OBJECT-TYPE
			SYNTAX	INTEGER
			MAX-ACCESS	read-only
			STATUS	current
			::= { hmWanMbusD5 91 }

hmWanMbusD5VIF2B		OBJECT-TYPE
			SYNTAX	INTEGER
			MAX-ACCESS	read-only
			STATUS	current
			::= { hmWanMbusD5 92 }

hmWanMbusD5Value2B		OBJECT-TYPE
			SYNTAX	INTEGER
			MAX-ACCESS	read-only
			STATUS	current
			::= { hmWanMbusD5 93 }

hmWanMbusD5VIF2C		OBJECT-TYPE
			SYNTAX	INTEGER
			MAX-ACCESS	read-only
			STATUS	current
			::= { hmWanMbusD5 94 }

hmWanMbusD5Value2C		OBJECT-TYPE
			SYNTAX	INTEGER
			MAX-ACCESS	read-only
			STATUS	current
			::= { hmWanMbusD5 95 }

hmWanMbusD5VIF2D		OBJECT-TYPE
			SYNTAX	INTEGER
			MAX-ACCESS	read-only
			STATUS	current
			::= { hmWanMbusD5 96 }

hmWanMbusD5Value2D		OBJECT-TYPE
			SYNTAX	INTEGER
			MAX-ACCESS	read-only
			STATUS	current
			::= { hmWanMbusD5 97 }

hmWanMbusD5VIF2E		OBJECT-TYPE
			SYNTAX	INTEGER
			MAX-ACCESS	read-only
			STATUS	current
			::= { hmWanMbusD5 98 }

hmWanMbusD5Value2E		OBJECT-TYPE
			SYNTAX	INTEGER
			MAX-ACCESS	read-only
			STATUS	current
			::= { hmWanMbusD5 99 }

hmWanMbusD5VIF2F		OBJECT-TYPE
			SYNTAX	INTEGER
			MAX-ACCESS	read-only
			STATUS	current
			::= { hmWanMbusD5 100 }

hmWanMbusD5Value2F		OBJECT-TYPE
			SYNTAX	INTEGER
			MAX-ACCESS	read-only
			STATUS	current
			::= { hmWanMbusD5 101 }

hmWanMbusD6			OBJECT IDENTIFIER ::= { hmWanMbus 214 }

hmWanMbusD6IdNumber		OBJECT-TYPE
			SYNTAX	Gauge32
			MAX-ACCESS	read-only
			STATUS	current
			::= { hmWanMbusD6 1 }

hmWanMbusD6Manufacturer	OBJECT-TYPE
			SYNTAX	Gauge32
			MAX-ACCESS	read-only
			STATUS	current
			::= { hmWanMbusD6 2 }

hmWanMbusD6Version		OBJECT-TYPE
			SYNTAX	Gauge32
			MAX-ACCESS	read-only
			STATUS	current
			::= { hmWanMbusD6 3 }

hmWanMbusD6Medium		OBJECT-TYPE
			SYNTAX	Gauge32
			MAX-ACCESS	read-only
			STATUS	current
			::= { hmWanMbusD6 4 }

hmWanMbusD6Status		OBJECT-TYPE
			SYNTAX	Gauge32
			MAX-ACCESS	read-only
			STATUS	current
			::= { hmWanMbusD6 5 }

hmWanMbusD6VIF00		OBJECT-TYPE
			SYNTAX	INTEGER
			MAX-ACCESS	read-only
			STATUS	current
			::= { hmWanMbusD6 6 }

hmWanMbusD6Value00		OBJECT-TYPE
			SYNTAX	INTEGER
			MAX-ACCESS	read-only
			STATUS	current
			::= { hmWanMbusD6 7 }

hmWanMbusD6VIF01		OBJECT-TYPE
			SYNTAX	INTEGER
			MAX-ACCESS	read-only
			STATUS	current
			::= { hmWanMbusD6 8 }

hmWanMbusD6Value01		OBJECT-TYPE
			SYNTAX	INTEGER
			MAX-ACCESS	read-only
			STATUS	current
			::= { hmWanMbusD6 9 }

hmWanMbusD6VIF02		OBJECT-TYPE
			SYNTAX	INTEGER
			MAX-ACCESS	read-only
			STATUS	current
			::= { hmWanMbusD6 10 }

hmWanMbusD6Value02		OBJECT-TYPE
			SYNTAX	INTEGER
			MAX-ACCESS	read-only
			STATUS	current
			::= { hmWanMbusD6 11 }

hmWanMbusD6VIF03		OBJECT-TYPE
			SYNTAX	INTEGER
			MAX-ACCESS	read-only
			STATUS	current
			::= { hmWanMbusD6 12 }

hmWanMbusD6Value03		OBJECT-TYPE
			SYNTAX	INTEGER
			MAX-ACCESS	read-only
			STATUS	current
			::= { hmWanMbusD6 13 }

hmWanMbusD6VIF04		OBJECT-TYPE
			SYNTAX	INTEGER
			MAX-ACCESS	read-only
			STATUS	current
			::= { hmWanMbusD6 14 }

hmWanMbusD6Value04		OBJECT-TYPE
			SYNTAX	INTEGER
			MAX-ACCESS	read-only
			STATUS	current
			::= { hmWanMbusD6 15 }

hmWanMbusD6VIF05		OBJECT-TYPE
			SYNTAX	INTEGER
			MAX-ACCESS	read-only
			STATUS	current
			::= { hmWanMbusD6 16 }

hmWanMbusD6Value05		OBJECT-TYPE
			SYNTAX	INTEGER
			MAX-ACCESS	read-only
			STATUS	current
			::= { hmWanMbusD6 17 }

hmWanMbusD6VIF06		OBJECT-TYPE
			SYNTAX	INTEGER
			MAX-ACCESS	read-only
			STATUS	current
			::= { hmWanMbusD6 18 }

hmWanMbusD6Value06		OBJECT-TYPE
			SYNTAX	INTEGER
			MAX-ACCESS	read-only
			STATUS	current
			::= { hmWanMbusD6 19 }

hmWanMbusD6VIF07		OBJECT-TYPE
			SYNTAX	INTEGER
			MAX-ACCESS	read-only
			STATUS	current
			::= { hmWanMbusD6 20 }

hmWanMbusD6Value07		OBJECT-TYPE
			SYNTAX	INTEGER
			MAX-ACCESS	read-only
			STATUS	current
			::= { hmWanMbusD6 21 }

hmWanMbusD6VIF08		OBJECT-TYPE
			SYNTAX	INTEGER
			MAX-ACCESS	read-only
			STATUS	current
			::= { hmWanMbusD6 22 }

hmWanMbusD6Value08		OBJECT-TYPE
			SYNTAX	INTEGER
			MAX-ACCESS	read-only
			STATUS	current
			::= { hmWanMbusD6 23 }

hmWanMbusD6VIF09		OBJECT-TYPE
			SYNTAX	INTEGER
			MAX-ACCESS	read-only
			STATUS	current
			::= { hmWanMbusD6 24 }

hmWanMbusD6Value09		OBJECT-TYPE
			SYNTAX	INTEGER
			MAX-ACCESS	read-only
			STATUS	current
			::= { hmWanMbusD6 25 }

hmWanMbusD6VIF0A		OBJECT-TYPE
			SYNTAX	INTEGER
			MAX-ACCESS	read-only
			STATUS	current
			::= { hmWanMbusD6 26 }

hmWanMbusD6Value0A		OBJECT-TYPE
			SYNTAX	INTEGER
			MAX-ACCESS	read-only
			STATUS	current
			::= { hmWanMbusD6 27 }

hmWanMbusD6VIF0B		OBJECT-TYPE
			SYNTAX	INTEGER
			MAX-ACCESS	read-only
			STATUS	current
			::= { hmWanMbusD6 28 }

hmWanMbusD6Value0B		OBJECT-TYPE
			SYNTAX	INTEGER
			MAX-ACCESS	read-only
			STATUS	current
			::= { hmWanMbusD6 29 }

hmWanMbusD6VIF0C		OBJECT-TYPE
			SYNTAX	INTEGER
			MAX-ACCESS	read-only
			STATUS	current
			::= { hmWanMbusD6 30 }

hmWanMbusD6Value0C		OBJECT-TYPE
			SYNTAX	INTEGER
			MAX-ACCESS	read-only
			STATUS	current
			::= { hmWanMbusD6 31 }

hmWanMbusD6VIF0D		OBJECT-TYPE
			SYNTAX	INTEGER
			MAX-ACCESS	read-only
			STATUS	current
			::= { hmWanMbusD6 32 }

hmWanMbusD6Value0D		OBJECT-TYPE
			SYNTAX	INTEGER
			MAX-ACCESS	read-only
			STATUS	current
			::= { hmWanMbusD6 33 }

hmWanMbusD6VIF0E		OBJECT-TYPE
			SYNTAX	INTEGER
			MAX-ACCESS	read-only
			STATUS	current
			::= { hmWanMbusD6 34 }

hmWanMbusD6Value0E		OBJECT-TYPE
			SYNTAX	INTEGER
			MAX-ACCESS	read-only
			STATUS	current
			::= { hmWanMbusD6 35 }

hmWanMbusD6VIF0F		OBJECT-TYPE
			SYNTAX	INTEGER
			MAX-ACCESS	read-only
			STATUS	current
			::= { hmWanMbusD6 36 }

hmWanMbusD6Value0F		OBJECT-TYPE
			SYNTAX	INTEGER
			MAX-ACCESS	read-only
			STATUS	current
			::= { hmWanMbusD6 37 }

hmWanMbusD6VIF10		OBJECT-TYPE
			SYNTAX	INTEGER
			MAX-ACCESS	read-only
			STATUS	current
			::= { hmWanMbusD6 38 }

hmWanMbusD6Value10		OBJECT-TYPE
			SYNTAX	INTEGER
			MAX-ACCESS	read-only
			STATUS	current
			::= { hmWanMbusD6 39 }

hmWanMbusD6VIF11		OBJECT-TYPE
			SYNTAX	INTEGER
			MAX-ACCESS	read-only
			STATUS	current
			::= { hmWanMbusD6 40 }

hmWanMbusD6Value11		OBJECT-TYPE
			SYNTAX	INTEGER
			MAX-ACCESS	read-only
			STATUS	current
			::= { hmWanMbusD6 41 }

hmWanMbusD6VIF12		OBJECT-TYPE
			SYNTAX	INTEGER
			MAX-ACCESS	read-only
			STATUS	current
			::= { hmWanMbusD6 42 }

hmWanMbusD6Value12		OBJECT-TYPE
			SYNTAX	INTEGER
			MAX-ACCESS	read-only
			STATUS	current
			::= { hmWanMbusD6 43 }

hmWanMbusD6VIF13		OBJECT-TYPE
			SYNTAX	INTEGER
			MAX-ACCESS	read-only
			STATUS	current
			::= { hmWanMbusD6 44 }

hmWanMbusD6Value13		OBJECT-TYPE
			SYNTAX	INTEGER
			MAX-ACCESS	read-only
			STATUS	current
			::= { hmWanMbusD6 45 }

hmWanMbusD6VIF14		OBJECT-TYPE
			SYNTAX	INTEGER
			MAX-ACCESS	read-only
			STATUS	current
			::= { hmWanMbusD6 46 }

hmWanMbusD6Value14		OBJECT-TYPE
			SYNTAX	INTEGER
			MAX-ACCESS	read-only
			STATUS	current
			::= { hmWanMbusD6 47 }

hmWanMbusD6VIF15		OBJECT-TYPE
			SYNTAX	INTEGER
			MAX-ACCESS	read-only
			STATUS	current
			::= { hmWanMbusD6 48 }

hmWanMbusD6Value15		OBJECT-TYPE
			SYNTAX	INTEGER
			MAX-ACCESS	read-only
			STATUS	current
			::= { hmWanMbusD6 49 }

hmWanMbusD6VIF16		OBJECT-TYPE
			SYNTAX	INTEGER
			MAX-ACCESS	read-only
			STATUS	current
			::= { hmWanMbusD6 50 }

hmWanMbusD6Value16		OBJECT-TYPE
			SYNTAX	INTEGER
			MAX-ACCESS	read-only
			STATUS	current
			::= { hmWanMbusD6 51 }

hmWanMbusD6VIF17		OBJECT-TYPE
			SYNTAX	INTEGER
			MAX-ACCESS	read-only
			STATUS	current
			::= { hmWanMbusD6 52 }

hmWanMbusD6Value17		OBJECT-TYPE
			SYNTAX	INTEGER
			MAX-ACCESS	read-only
			STATUS	current
			::= { hmWanMbusD6 53 }

hmWanMbusD6VIF18		OBJECT-TYPE
			SYNTAX	INTEGER
			MAX-ACCESS	read-only
			STATUS	current
			::= { hmWanMbusD6 54 }

hmWanMbusD6Value18		OBJECT-TYPE
			SYNTAX	INTEGER
			MAX-ACCESS	read-only
			STATUS	current
			::= { hmWanMbusD6 55 }

hmWanMbusD6VIF19		OBJECT-TYPE
			SYNTAX	INTEGER
			MAX-ACCESS	read-only
			STATUS	current
			::= { hmWanMbusD6 56 }

hmWanMbusD6Value19		OBJECT-TYPE
			SYNTAX	INTEGER
			MAX-ACCESS	read-only
			STATUS	current
			::= { hmWanMbusD6 57 }

hmWanMbusD6VIF1A		OBJECT-TYPE
			SYNTAX	INTEGER
			MAX-ACCESS	read-only
			STATUS	current
			::= { hmWanMbusD6 58 }

hmWanMbusD6Value1A		OBJECT-TYPE
			SYNTAX	INTEGER
			MAX-ACCESS	read-only
			STATUS	current
			::= { hmWanMbusD6 59 }

hmWanMbusD6VIF1B		OBJECT-TYPE
			SYNTAX	INTEGER
			MAX-ACCESS	read-only
			STATUS	current
			::= { hmWanMbusD6 60 }

hmWanMbusD6Value1B		OBJECT-TYPE
			SYNTAX	INTEGER
			MAX-ACCESS	read-only
			STATUS	current
			::= { hmWanMbusD6 61 }

hmWanMbusD6VIF1C		OBJECT-TYPE
			SYNTAX	INTEGER
			MAX-ACCESS	read-only
			STATUS	current
			::= { hmWanMbusD6 62 }

hmWanMbusD6Value1C		OBJECT-TYPE
			SYNTAX	INTEGER
			MAX-ACCESS	read-only
			STATUS	current
			::= { hmWanMbusD6 63 }

hmWanMbusD6VIF1D		OBJECT-TYPE
			SYNTAX	INTEGER
			MAX-ACCESS	read-only
			STATUS	current
			::= { hmWanMbusD6 64 }

hmWanMbusD6Value1D		OBJECT-TYPE
			SYNTAX	INTEGER
			MAX-ACCESS	read-only
			STATUS	current
			::= { hmWanMbusD6 65 }

hmWanMbusD6VIF1E		OBJECT-TYPE
			SYNTAX	INTEGER
			MAX-ACCESS	read-only
			STATUS	current
			::= { hmWanMbusD6 66 }

hmWanMbusD6Value1E		OBJECT-TYPE
			SYNTAX	INTEGER
			MAX-ACCESS	read-only
			STATUS	current
			::= { hmWanMbusD6 67 }

hmWanMbusD6VIF1F		OBJECT-TYPE
			SYNTAX	INTEGER
			MAX-ACCESS	read-only
			STATUS	current
			::= { hmWanMbusD6 68 }

hmWanMbusD6Value1F		OBJECT-TYPE
			SYNTAX	INTEGER
			MAX-ACCESS	read-only
			STATUS	current
			::= { hmWanMbusD6 69 }

hmWanMbusD6VIF20		OBJECT-TYPE
			SYNTAX	INTEGER
			MAX-ACCESS	read-only
			STATUS	current
			::= { hmWanMbusD6 70 }

hmWanMbusD6Value20		OBJECT-TYPE
			SYNTAX	INTEGER
			MAX-ACCESS	read-only
			STATUS	current
			::= { hmWanMbusD6 71 }

hmWanMbusD6VIF21		OBJECT-TYPE
			SYNTAX	INTEGER
			MAX-ACCESS	read-only
			STATUS	current
			::= { hmWanMbusD6 72 }

hmWanMbusD6Value21		OBJECT-TYPE
			SYNTAX	INTEGER
			MAX-ACCESS	read-only
			STATUS	current
			::= { hmWanMbusD6 73 }

hmWanMbusD6VIF22		OBJECT-TYPE
			SYNTAX	INTEGER
			MAX-ACCESS	read-only
			STATUS	current
			::= { hmWanMbusD6 74 }

hmWanMbusD6Value22		OBJECT-TYPE
			SYNTAX	INTEGER
			MAX-ACCESS	read-only
			STATUS	current
			::= { hmWanMbusD6 75 }

hmWanMbusD6VIF23		OBJECT-TYPE
			SYNTAX	INTEGER
			MAX-ACCESS	read-only
			STATUS	current
			::= { hmWanMbusD6 76 }

hmWanMbusD6Value23		OBJECT-TYPE
			SYNTAX	INTEGER
			MAX-ACCESS	read-only
			STATUS	current
			::= { hmWanMbusD6 77 }

hmWanMbusD6VIF24		OBJECT-TYPE
			SYNTAX	INTEGER
			MAX-ACCESS	read-only
			STATUS	current
			::= { hmWanMbusD6 78 }

hmWanMbusD6Value24		OBJECT-TYPE
			SYNTAX	INTEGER
			MAX-ACCESS	read-only
			STATUS	current
			::= { hmWanMbusD6 79 }

hmWanMbusD6VIF25		OBJECT-TYPE
			SYNTAX	INTEGER
			MAX-ACCESS	read-only
			STATUS	current
			::= { hmWanMbusD6 80 }

hmWanMbusD6Value25		OBJECT-TYPE
			SYNTAX	INTEGER
			MAX-ACCESS	read-only
			STATUS	current
			::= { hmWanMbusD6 81 }

hmWanMbusD6VIF26		OBJECT-TYPE
			SYNTAX	INTEGER
			MAX-ACCESS	read-only
			STATUS	current
			::= { hmWanMbusD6 82 }

hmWanMbusD6Value26		OBJECT-TYPE
			SYNTAX	INTEGER
			MAX-ACCESS	read-only
			STATUS	current
			::= { hmWanMbusD6 83 }

hmWanMbusD6VIF27		OBJECT-TYPE
			SYNTAX	INTEGER
			MAX-ACCESS	read-only
			STATUS	current
			::= { hmWanMbusD6 84 }

hmWanMbusD6Value27		OBJECT-TYPE
			SYNTAX	INTEGER
			MAX-ACCESS	read-only
			STATUS	current
			::= { hmWanMbusD6 85 }

hmWanMbusD6VIF28		OBJECT-TYPE
			SYNTAX	INTEGER
			MAX-ACCESS	read-only
			STATUS	current
			::= { hmWanMbusD6 86 }

hmWanMbusD6Value28		OBJECT-TYPE
			SYNTAX	INTEGER
			MAX-ACCESS	read-only
			STATUS	current
			::= { hmWanMbusD6 87 }

hmWanMbusD6VIF29		OBJECT-TYPE
			SYNTAX	INTEGER
			MAX-ACCESS	read-only
			STATUS	current
			::= { hmWanMbusD6 88 }

hmWanMbusD6Value29		OBJECT-TYPE
			SYNTAX	INTEGER
			MAX-ACCESS	read-only
			STATUS	current
			::= { hmWanMbusD6 89 }

hmWanMbusD6VIF2A		OBJECT-TYPE
			SYNTAX	INTEGER
			MAX-ACCESS	read-only
			STATUS	current
			::= { hmWanMbusD6 90 }

hmWanMbusD6Value2A		OBJECT-TYPE
			SYNTAX	INTEGER
			MAX-ACCESS	read-only
			STATUS	current
			::= { hmWanMbusD6 91 }

hmWanMbusD6VIF2B		OBJECT-TYPE
			SYNTAX	INTEGER
			MAX-ACCESS	read-only
			STATUS	current
			::= { hmWanMbusD6 92 }

hmWanMbusD6Value2B		OBJECT-TYPE
			SYNTAX	INTEGER
			MAX-ACCESS	read-only
			STATUS	current
			::= { hmWanMbusD6 93 }

hmWanMbusD6VIF2C		OBJECT-TYPE
			SYNTAX	INTEGER
			MAX-ACCESS	read-only
			STATUS	current
			::= { hmWanMbusD6 94 }

hmWanMbusD6Value2C		OBJECT-TYPE
			SYNTAX	INTEGER
			MAX-ACCESS	read-only
			STATUS	current
			::= { hmWanMbusD6 95 }

hmWanMbusD6VIF2D		OBJECT-TYPE
			SYNTAX	INTEGER
			MAX-ACCESS	read-only
			STATUS	current
			::= { hmWanMbusD6 96 }

hmWanMbusD6Value2D		OBJECT-TYPE
			SYNTAX	INTEGER
			MAX-ACCESS	read-only
			STATUS	current
			::= { hmWanMbusD6 97 }

hmWanMbusD6VIF2E		OBJECT-TYPE
			SYNTAX	INTEGER
			MAX-ACCESS	read-only
			STATUS	current
			::= { hmWanMbusD6 98 }

hmWanMbusD6Value2E		OBJECT-TYPE
			SYNTAX	INTEGER
			MAX-ACCESS	read-only
			STATUS	current
			::= { hmWanMbusD6 99 }

hmWanMbusD6VIF2F		OBJECT-TYPE
			SYNTAX	INTEGER
			MAX-ACCESS	read-only
			STATUS	current
			::= { hmWanMbusD6 100 }

hmWanMbusD6Value2F		OBJECT-TYPE
			SYNTAX	INTEGER
			MAX-ACCESS	read-only
			STATUS	current
			::= { hmWanMbusD6 101 }

hmWanMbusD7			OBJECT IDENTIFIER ::= { hmWanMbus 215 }

hmWanMbusD7IdNumber		OBJECT-TYPE
			SYNTAX	Gauge32
			MAX-ACCESS	read-only
			STATUS	current
			::= { hmWanMbusD7 1 }

hmWanMbusD7Manufacturer	OBJECT-TYPE
			SYNTAX	Gauge32
			MAX-ACCESS	read-only
			STATUS	current
			::= { hmWanMbusD7 2 }

hmWanMbusD7Version		OBJECT-TYPE
			SYNTAX	Gauge32
			MAX-ACCESS	read-only
			STATUS	current
			::= { hmWanMbusD7 3 }

hmWanMbusD7Medium		OBJECT-TYPE
			SYNTAX	Gauge32
			MAX-ACCESS	read-only
			STATUS	current
			::= { hmWanMbusD7 4 }

hmWanMbusD7Status		OBJECT-TYPE
			SYNTAX	Gauge32
			MAX-ACCESS	read-only
			STATUS	current
			::= { hmWanMbusD7 5 }

hmWanMbusD7VIF00		OBJECT-TYPE
			SYNTAX	INTEGER
			MAX-ACCESS	read-only
			STATUS	current
			::= { hmWanMbusD7 6 }

hmWanMbusD7Value00		OBJECT-TYPE
			SYNTAX	INTEGER
			MAX-ACCESS	read-only
			STATUS	current
			::= { hmWanMbusD7 7 }

hmWanMbusD7VIF01		OBJECT-TYPE
			SYNTAX	INTEGER
			MAX-ACCESS	read-only
			STATUS	current
			::= { hmWanMbusD7 8 }

hmWanMbusD7Value01		OBJECT-TYPE
			SYNTAX	INTEGER
			MAX-ACCESS	read-only
			STATUS	current
			::= { hmWanMbusD7 9 }

hmWanMbusD7VIF02		OBJECT-TYPE
			SYNTAX	INTEGER
			MAX-ACCESS	read-only
			STATUS	current
			::= { hmWanMbusD7 10 }

hmWanMbusD7Value02		OBJECT-TYPE
			SYNTAX	INTEGER
			MAX-ACCESS	read-only
			STATUS	current
			::= { hmWanMbusD7 11 }

hmWanMbusD7VIF03		OBJECT-TYPE
			SYNTAX	INTEGER
			MAX-ACCESS	read-only
			STATUS	current
			::= { hmWanMbusD7 12 }

hmWanMbusD7Value03		OBJECT-TYPE
			SYNTAX	INTEGER
			MAX-ACCESS	read-only
			STATUS	current
			::= { hmWanMbusD7 13 }

hmWanMbusD7VIF04		OBJECT-TYPE
			SYNTAX	INTEGER
			MAX-ACCESS	read-only
			STATUS	current
			::= { hmWanMbusD7 14 }

hmWanMbusD7Value04		OBJECT-TYPE
			SYNTAX	INTEGER
			MAX-ACCESS	read-only
			STATUS	current
			::= { hmWanMbusD7 15 }

hmWanMbusD7VIF05		OBJECT-TYPE
			SYNTAX	INTEGER
			MAX-ACCESS	read-only
			STATUS	current
			::= { hmWanMbusD7 16 }

hmWanMbusD7Value05		OBJECT-TYPE
			SYNTAX	INTEGER
			MAX-ACCESS	read-only
			STATUS	current
			::= { hmWanMbusD7 17 }

hmWanMbusD7VIF06		OBJECT-TYPE
			SYNTAX	INTEGER
			MAX-ACCESS	read-only
			STATUS	current
			::= { hmWanMbusD7 18 }

hmWanMbusD7Value06		OBJECT-TYPE
			SYNTAX	INTEGER
			MAX-ACCESS	read-only
			STATUS	current
			::= { hmWanMbusD7 19 }

hmWanMbusD7VIF07		OBJECT-TYPE
			SYNTAX	INTEGER
			MAX-ACCESS	read-only
			STATUS	current
			::= { hmWanMbusD7 20 }

hmWanMbusD7Value07		OBJECT-TYPE
			SYNTAX	INTEGER
			MAX-ACCESS	read-only
			STATUS	current
			::= { hmWanMbusD7 21 }

hmWanMbusD7VIF08		OBJECT-TYPE
			SYNTAX	INTEGER
			MAX-ACCESS	read-only
			STATUS	current
			::= { hmWanMbusD7 22 }

hmWanMbusD7Value08		OBJECT-TYPE
			SYNTAX	INTEGER
			MAX-ACCESS	read-only
			STATUS	current
			::= { hmWanMbusD7 23 }

hmWanMbusD7VIF09		OBJECT-TYPE
			SYNTAX	INTEGER
			MAX-ACCESS	read-only
			STATUS	current
			::= { hmWanMbusD7 24 }

hmWanMbusD7Value09		OBJECT-TYPE
			SYNTAX	INTEGER
			MAX-ACCESS	read-only
			STATUS	current
			::= { hmWanMbusD7 25 }

hmWanMbusD7VIF0A		OBJECT-TYPE
			SYNTAX	INTEGER
			MAX-ACCESS	read-only
			STATUS	current
			::= { hmWanMbusD7 26 }

hmWanMbusD7Value0A		OBJECT-TYPE
			SYNTAX	INTEGER
			MAX-ACCESS	read-only
			STATUS	current
			::= { hmWanMbusD7 27 }

hmWanMbusD7VIF0B		OBJECT-TYPE
			SYNTAX	INTEGER
			MAX-ACCESS	read-only
			STATUS	current
			::= { hmWanMbusD7 28 }

hmWanMbusD7Value0B		OBJECT-TYPE
			SYNTAX	INTEGER
			MAX-ACCESS	read-only
			STATUS	current
			::= { hmWanMbusD7 29 }

hmWanMbusD7VIF0C		OBJECT-TYPE
			SYNTAX	INTEGER
			MAX-ACCESS	read-only
			STATUS	current
			::= { hmWanMbusD7 30 }

hmWanMbusD7Value0C		OBJECT-TYPE
			SYNTAX	INTEGER
			MAX-ACCESS	read-only
			STATUS	current
			::= { hmWanMbusD7 31 }

hmWanMbusD7VIF0D		OBJECT-TYPE
			SYNTAX	INTEGER
			MAX-ACCESS	read-only
			STATUS	current
			::= { hmWanMbusD7 32 }

hmWanMbusD7Value0D		OBJECT-TYPE
			SYNTAX	INTEGER
			MAX-ACCESS	read-only
			STATUS	current
			::= { hmWanMbusD7 33 }

hmWanMbusD7VIF0E		OBJECT-TYPE
			SYNTAX	INTEGER
			MAX-ACCESS	read-only
			STATUS	current
			::= { hmWanMbusD7 34 }

hmWanMbusD7Value0E		OBJECT-TYPE
			SYNTAX	INTEGER
			MAX-ACCESS	read-only
			STATUS	current
			::= { hmWanMbusD7 35 }

hmWanMbusD7VIF0F		OBJECT-TYPE
			SYNTAX	INTEGER
			MAX-ACCESS	read-only
			STATUS	current
			::= { hmWanMbusD7 36 }

hmWanMbusD7Value0F		OBJECT-TYPE
			SYNTAX	INTEGER
			MAX-ACCESS	read-only
			STATUS	current
			::= { hmWanMbusD7 37 }

hmWanMbusD7VIF10		OBJECT-TYPE
			SYNTAX	INTEGER
			MAX-ACCESS	read-only
			STATUS	current
			::= { hmWanMbusD7 38 }

hmWanMbusD7Value10		OBJECT-TYPE
			SYNTAX	INTEGER
			MAX-ACCESS	read-only
			STATUS	current
			::= { hmWanMbusD7 39 }

hmWanMbusD7VIF11		OBJECT-TYPE
			SYNTAX	INTEGER
			MAX-ACCESS	read-only
			STATUS	current
			::= { hmWanMbusD7 40 }

hmWanMbusD7Value11		OBJECT-TYPE
			SYNTAX	INTEGER
			MAX-ACCESS	read-only
			STATUS	current
			::= { hmWanMbusD7 41 }

hmWanMbusD7VIF12		OBJECT-TYPE
			SYNTAX	INTEGER
			MAX-ACCESS	read-only
			STATUS	current
			::= { hmWanMbusD7 42 }

hmWanMbusD7Value12		OBJECT-TYPE
			SYNTAX	INTEGER
			MAX-ACCESS	read-only
			STATUS	current
			::= { hmWanMbusD7 43 }

hmWanMbusD7VIF13		OBJECT-TYPE
			SYNTAX	INTEGER
			MAX-ACCESS	read-only
			STATUS	current
			::= { hmWanMbusD7 44 }

hmWanMbusD7Value13		OBJECT-TYPE
			SYNTAX	INTEGER
			MAX-ACCESS	read-only
			STATUS	current
			::= { hmWanMbusD7 45 }

hmWanMbusD7VIF14		OBJECT-TYPE
			SYNTAX	INTEGER
			MAX-ACCESS	read-only
			STATUS	current
			::= { hmWanMbusD7 46 }

hmWanMbusD7Value14		OBJECT-TYPE
			SYNTAX	INTEGER
			MAX-ACCESS	read-only
			STATUS	current
			::= { hmWanMbusD7 47 }

hmWanMbusD7VIF15		OBJECT-TYPE
			SYNTAX	INTEGER
			MAX-ACCESS	read-only
			STATUS	current
			::= { hmWanMbusD7 48 }

hmWanMbusD7Value15		OBJECT-TYPE
			SYNTAX	INTEGER
			MAX-ACCESS	read-only
			STATUS	current
			::= { hmWanMbusD7 49 }

hmWanMbusD7VIF16		OBJECT-TYPE
			SYNTAX	INTEGER
			MAX-ACCESS	read-only
			STATUS	current
			::= { hmWanMbusD7 50 }

hmWanMbusD7Value16		OBJECT-TYPE
			SYNTAX	INTEGER
			MAX-ACCESS	read-only
			STATUS	current
			::= { hmWanMbusD7 51 }

hmWanMbusD7VIF17		OBJECT-TYPE
			SYNTAX	INTEGER
			MAX-ACCESS	read-only
			STATUS	current
			::= { hmWanMbusD7 52 }

hmWanMbusD7Value17		OBJECT-TYPE
			SYNTAX	INTEGER
			MAX-ACCESS	read-only
			STATUS	current
			::= { hmWanMbusD7 53 }

hmWanMbusD7VIF18		OBJECT-TYPE
			SYNTAX	INTEGER
			MAX-ACCESS	read-only
			STATUS	current
			::= { hmWanMbusD7 54 }

hmWanMbusD7Value18		OBJECT-TYPE
			SYNTAX	INTEGER
			MAX-ACCESS	read-only
			STATUS	current
			::= { hmWanMbusD7 55 }

hmWanMbusD7VIF19		OBJECT-TYPE
			SYNTAX	INTEGER
			MAX-ACCESS	read-only
			STATUS	current
			::= { hmWanMbusD7 56 }

hmWanMbusD7Value19		OBJECT-TYPE
			SYNTAX	INTEGER
			MAX-ACCESS	read-only
			STATUS	current
			::= { hmWanMbusD7 57 }

hmWanMbusD7VIF1A		OBJECT-TYPE
			SYNTAX	INTEGER
			MAX-ACCESS	read-only
			STATUS	current
			::= { hmWanMbusD7 58 }

hmWanMbusD7Value1A		OBJECT-TYPE
			SYNTAX	INTEGER
			MAX-ACCESS	read-only
			STATUS	current
			::= { hmWanMbusD7 59 }

hmWanMbusD7VIF1B		OBJECT-TYPE
			SYNTAX	INTEGER
			MAX-ACCESS	read-only
			STATUS	current
			::= { hmWanMbusD7 60 }

hmWanMbusD7Value1B		OBJECT-TYPE
			SYNTAX	INTEGER
			MAX-ACCESS	read-only
			STATUS	current
			::= { hmWanMbusD7 61 }

hmWanMbusD7VIF1C		OBJECT-TYPE
			SYNTAX	INTEGER
			MAX-ACCESS	read-only
			STATUS	current
			::= { hmWanMbusD7 62 }

hmWanMbusD7Value1C		OBJECT-TYPE
			SYNTAX	INTEGER
			MAX-ACCESS	read-only
			STATUS	current
			::= { hmWanMbusD7 63 }

hmWanMbusD7VIF1D		OBJECT-TYPE
			SYNTAX	INTEGER
			MAX-ACCESS	read-only
			STATUS	current
			::= { hmWanMbusD7 64 }

hmWanMbusD7Value1D		OBJECT-TYPE
			SYNTAX	INTEGER
			MAX-ACCESS	read-only
			STATUS	current
			::= { hmWanMbusD7 65 }

hmWanMbusD7VIF1E		OBJECT-TYPE
			SYNTAX	INTEGER
			MAX-ACCESS	read-only
			STATUS	current
			::= { hmWanMbusD7 66 }

hmWanMbusD7Value1E		OBJECT-TYPE
			SYNTAX	INTEGER
			MAX-ACCESS	read-only
			STATUS	current
			::= { hmWanMbusD7 67 }

hmWanMbusD7VIF1F		OBJECT-TYPE
			SYNTAX	INTEGER
			MAX-ACCESS	read-only
			STATUS	current
			::= { hmWanMbusD7 68 }

hmWanMbusD7Value1F		OBJECT-TYPE
			SYNTAX	INTEGER
			MAX-ACCESS	read-only
			STATUS	current
			::= { hmWanMbusD7 69 }

hmWanMbusD7VIF20		OBJECT-TYPE
			SYNTAX	INTEGER
			MAX-ACCESS	read-only
			STATUS	current
			::= { hmWanMbusD7 70 }

hmWanMbusD7Value20		OBJECT-TYPE
			SYNTAX	INTEGER
			MAX-ACCESS	read-only
			STATUS	current
			::= { hmWanMbusD7 71 }

hmWanMbusD7VIF21		OBJECT-TYPE
			SYNTAX	INTEGER
			MAX-ACCESS	read-only
			STATUS	current
			::= { hmWanMbusD7 72 }

hmWanMbusD7Value21		OBJECT-TYPE
			SYNTAX	INTEGER
			MAX-ACCESS	read-only
			STATUS	current
			::= { hmWanMbusD7 73 }

hmWanMbusD7VIF22		OBJECT-TYPE
			SYNTAX	INTEGER
			MAX-ACCESS	read-only
			STATUS	current
			::= { hmWanMbusD7 74 }

hmWanMbusD7Value22		OBJECT-TYPE
			SYNTAX	INTEGER
			MAX-ACCESS	read-only
			STATUS	current
			::= { hmWanMbusD7 75 }

hmWanMbusD7VIF23		OBJECT-TYPE
			SYNTAX	INTEGER
			MAX-ACCESS	read-only
			STATUS	current
			::= { hmWanMbusD7 76 }

hmWanMbusD7Value23		OBJECT-TYPE
			SYNTAX	INTEGER
			MAX-ACCESS	read-only
			STATUS	current
			::= { hmWanMbusD7 77 }

hmWanMbusD7VIF24		OBJECT-TYPE
			SYNTAX	INTEGER
			MAX-ACCESS	read-only
			STATUS	current
			::= { hmWanMbusD7 78 }

hmWanMbusD7Value24		OBJECT-TYPE
			SYNTAX	INTEGER
			MAX-ACCESS	read-only
			STATUS	current
			::= { hmWanMbusD7 79 }

hmWanMbusD7VIF25		OBJECT-TYPE
			SYNTAX	INTEGER
			MAX-ACCESS	read-only
			STATUS	current
			::= { hmWanMbusD7 80 }

hmWanMbusD7Value25		OBJECT-TYPE
			SYNTAX	INTEGER
			MAX-ACCESS	read-only
			STATUS	current
			::= { hmWanMbusD7 81 }

hmWanMbusD7VIF26		OBJECT-TYPE
			SYNTAX	INTEGER
			MAX-ACCESS	read-only
			STATUS	current
			::= { hmWanMbusD7 82 }

hmWanMbusD7Value26		OBJECT-TYPE
			SYNTAX	INTEGER
			MAX-ACCESS	read-only
			STATUS	current
			::= { hmWanMbusD7 83 }

hmWanMbusD7VIF27		OBJECT-TYPE
			SYNTAX	INTEGER
			MAX-ACCESS	read-only
			STATUS	current
			::= { hmWanMbusD7 84 }

hmWanMbusD7Value27		OBJECT-TYPE
			SYNTAX	INTEGER
			MAX-ACCESS	read-only
			STATUS	current
			::= { hmWanMbusD7 85 }

hmWanMbusD7VIF28		OBJECT-TYPE
			SYNTAX	INTEGER
			MAX-ACCESS	read-only
			STATUS	current
			::= { hmWanMbusD7 86 }

hmWanMbusD7Value28		OBJECT-TYPE
			SYNTAX	INTEGER
			MAX-ACCESS	read-only
			STATUS	current
			::= { hmWanMbusD7 87 }

hmWanMbusD7VIF29		OBJECT-TYPE
			SYNTAX	INTEGER
			MAX-ACCESS	read-only
			STATUS	current
			::= { hmWanMbusD7 88 }

hmWanMbusD7Value29		OBJECT-TYPE
			SYNTAX	INTEGER
			MAX-ACCESS	read-only
			STATUS	current
			::= { hmWanMbusD7 89 }

hmWanMbusD7VIF2A		OBJECT-TYPE
			SYNTAX	INTEGER
			MAX-ACCESS	read-only
			STATUS	current
			::= { hmWanMbusD7 90 }

hmWanMbusD7Value2A		OBJECT-TYPE
			SYNTAX	INTEGER
			MAX-ACCESS	read-only
			STATUS	current
			::= { hmWanMbusD7 91 }

hmWanMbusD7VIF2B		OBJECT-TYPE
			SYNTAX	INTEGER
			MAX-ACCESS	read-only
			STATUS	current
			::= { hmWanMbusD7 92 }

hmWanMbusD7Value2B		OBJECT-TYPE
			SYNTAX	INTEGER
			MAX-ACCESS	read-only
			STATUS	current
			::= { hmWanMbusD7 93 }

hmWanMbusD7VIF2C		OBJECT-TYPE
			SYNTAX	INTEGER
			MAX-ACCESS	read-only
			STATUS	current
			::= { hmWanMbusD7 94 }

hmWanMbusD7Value2C		OBJECT-TYPE
			SYNTAX	INTEGER
			MAX-ACCESS	read-only
			STATUS	current
			::= { hmWanMbusD7 95 }

hmWanMbusD7VIF2D		OBJECT-TYPE
			SYNTAX	INTEGER
			MAX-ACCESS	read-only
			STATUS	current
			::= { hmWanMbusD7 96 }

hmWanMbusD7Value2D		OBJECT-TYPE
			SYNTAX	INTEGER
			MAX-ACCESS	read-only
			STATUS	current
			::= { hmWanMbusD7 97 }

hmWanMbusD7VIF2E		OBJECT-TYPE
			SYNTAX	INTEGER
			MAX-ACCESS	read-only
			STATUS	current
			::= { hmWanMbusD7 98 }

hmWanMbusD7Value2E		OBJECT-TYPE
			SYNTAX	INTEGER
			MAX-ACCESS	read-only
			STATUS	current
			::= { hmWanMbusD7 99 }

hmWanMbusD7VIF2F		OBJECT-TYPE
			SYNTAX	INTEGER
			MAX-ACCESS	read-only
			STATUS	current
			::= { hmWanMbusD7 100 }

hmWanMbusD7Value2F		OBJECT-TYPE
			SYNTAX	INTEGER
			MAX-ACCESS	read-only
			STATUS	current
			::= { hmWanMbusD7 101 }

hmWanMbusD8			OBJECT IDENTIFIER ::= { hmWanMbus 216 }

hmWanMbusD8IdNumber		OBJECT-TYPE
			SYNTAX	Gauge32
			MAX-ACCESS	read-only
			STATUS	current
			::= { hmWanMbusD8 1 }

hmWanMbusD8Manufacturer	OBJECT-TYPE
			SYNTAX	Gauge32
			MAX-ACCESS	read-only
			STATUS	current
			::= { hmWanMbusD8 2 }

hmWanMbusD8Version		OBJECT-TYPE
			SYNTAX	Gauge32
			MAX-ACCESS	read-only
			STATUS	current
			::= { hmWanMbusD8 3 }

hmWanMbusD8Medium		OBJECT-TYPE
			SYNTAX	Gauge32
			MAX-ACCESS	read-only
			STATUS	current
			::= { hmWanMbusD8 4 }

hmWanMbusD8Status		OBJECT-TYPE
			SYNTAX	Gauge32
			MAX-ACCESS	read-only
			STATUS	current
			::= { hmWanMbusD8 5 }

hmWanMbusD8VIF00		OBJECT-TYPE
			SYNTAX	INTEGER
			MAX-ACCESS	read-only
			STATUS	current
			::= { hmWanMbusD8 6 }

hmWanMbusD8Value00		OBJECT-TYPE
			SYNTAX	INTEGER
			MAX-ACCESS	read-only
			STATUS	current
			::= { hmWanMbusD8 7 }

hmWanMbusD8VIF01		OBJECT-TYPE
			SYNTAX	INTEGER
			MAX-ACCESS	read-only
			STATUS	current
			::= { hmWanMbusD8 8 }

hmWanMbusD8Value01		OBJECT-TYPE
			SYNTAX	INTEGER
			MAX-ACCESS	read-only
			STATUS	current
			::= { hmWanMbusD8 9 }

hmWanMbusD8VIF02		OBJECT-TYPE
			SYNTAX	INTEGER
			MAX-ACCESS	read-only
			STATUS	current
			::= { hmWanMbusD8 10 }

hmWanMbusD8Value02		OBJECT-TYPE
			SYNTAX	INTEGER
			MAX-ACCESS	read-only
			STATUS	current
			::= { hmWanMbusD8 11 }

hmWanMbusD8VIF03		OBJECT-TYPE
			SYNTAX	INTEGER
			MAX-ACCESS	read-only
			STATUS	current
			::= { hmWanMbusD8 12 }

hmWanMbusD8Value03		OBJECT-TYPE
			SYNTAX	INTEGER
			MAX-ACCESS	read-only
			STATUS	current
			::= { hmWanMbusD8 13 }

hmWanMbusD8VIF04		OBJECT-TYPE
			SYNTAX	INTEGER
			MAX-ACCESS	read-only
			STATUS	current
			::= { hmWanMbusD8 14 }

hmWanMbusD8Value04		OBJECT-TYPE
			SYNTAX	INTEGER
			MAX-ACCESS	read-only
			STATUS	current
			::= { hmWanMbusD8 15 }

hmWanMbusD8VIF05		OBJECT-TYPE
			SYNTAX	INTEGER
			MAX-ACCESS	read-only
			STATUS	current
			::= { hmWanMbusD8 16 }

hmWanMbusD8Value05		OBJECT-TYPE
			SYNTAX	INTEGER
			MAX-ACCESS	read-only
			STATUS	current
			::= { hmWanMbusD8 17 }

hmWanMbusD8VIF06		OBJECT-TYPE
			SYNTAX	INTEGER
			MAX-ACCESS	read-only
			STATUS	current
			::= { hmWanMbusD8 18 }

hmWanMbusD8Value06		OBJECT-TYPE
			SYNTAX	INTEGER
			MAX-ACCESS	read-only
			STATUS	current
			::= { hmWanMbusD8 19 }

hmWanMbusD8VIF07		OBJECT-TYPE
			SYNTAX	INTEGER
			MAX-ACCESS	read-only
			STATUS	current
			::= { hmWanMbusD8 20 }

hmWanMbusD8Value07		OBJECT-TYPE
			SYNTAX	INTEGER
			MAX-ACCESS	read-only
			STATUS	current
			::= { hmWanMbusD8 21 }

hmWanMbusD8VIF08		OBJECT-TYPE
			SYNTAX	INTEGER
			MAX-ACCESS	read-only
			STATUS	current
			::= { hmWanMbusD8 22 }

hmWanMbusD8Value08		OBJECT-TYPE
			SYNTAX	INTEGER
			MAX-ACCESS	read-only
			STATUS	current
			::= { hmWanMbusD8 23 }

hmWanMbusD8VIF09		OBJECT-TYPE
			SYNTAX	INTEGER
			MAX-ACCESS	read-only
			STATUS	current
			::= { hmWanMbusD8 24 }

hmWanMbusD8Value09		OBJECT-TYPE
			SYNTAX	INTEGER
			MAX-ACCESS	read-only
			STATUS	current
			::= { hmWanMbusD8 25 }

hmWanMbusD8VIF0A		OBJECT-TYPE
			SYNTAX	INTEGER
			MAX-ACCESS	read-only
			STATUS	current
			::= { hmWanMbusD8 26 }

hmWanMbusD8Value0A		OBJECT-TYPE
			SYNTAX	INTEGER
			MAX-ACCESS	read-only
			STATUS	current
			::= { hmWanMbusD8 27 }

hmWanMbusD8VIF0B		OBJECT-TYPE
			SYNTAX	INTEGER
			MAX-ACCESS	read-only
			STATUS	current
			::= { hmWanMbusD8 28 }

hmWanMbusD8Value0B		OBJECT-TYPE
			SYNTAX	INTEGER
			MAX-ACCESS	read-only
			STATUS	current
			::= { hmWanMbusD8 29 }

hmWanMbusD8VIF0C		OBJECT-TYPE
			SYNTAX	INTEGER
			MAX-ACCESS	read-only
			STATUS	current
			::= { hmWanMbusD8 30 }

hmWanMbusD8Value0C		OBJECT-TYPE
			SYNTAX	INTEGER
			MAX-ACCESS	read-only
			STATUS	current
			::= { hmWanMbusD8 31 }

hmWanMbusD8VIF0D		OBJECT-TYPE
			SYNTAX	INTEGER
			MAX-ACCESS	read-only
			STATUS	current
			::= { hmWanMbusD8 32 }

hmWanMbusD8Value0D		OBJECT-TYPE
			SYNTAX	INTEGER
			MAX-ACCESS	read-only
			STATUS	current
			::= { hmWanMbusD8 33 }

hmWanMbusD8VIF0E		OBJECT-TYPE
			SYNTAX	INTEGER
			MAX-ACCESS	read-only
			STATUS	current
			::= { hmWanMbusD8 34 }

hmWanMbusD8Value0E		OBJECT-TYPE
			SYNTAX	INTEGER
			MAX-ACCESS	read-only
			STATUS	current
			::= { hmWanMbusD8 35 }

hmWanMbusD8VIF0F		OBJECT-TYPE
			SYNTAX	INTEGER
			MAX-ACCESS	read-only
			STATUS	current
			::= { hmWanMbusD8 36 }

hmWanMbusD8Value0F		OBJECT-TYPE
			SYNTAX	INTEGER
			MAX-ACCESS	read-only
			STATUS	current
			::= { hmWanMbusD8 37 }

hmWanMbusD8VIF10		OBJECT-TYPE
			SYNTAX	INTEGER
			MAX-ACCESS	read-only
			STATUS	current
			::= { hmWanMbusD8 38 }

hmWanMbusD8Value10		OBJECT-TYPE
			SYNTAX	INTEGER
			MAX-ACCESS	read-only
			STATUS	current
			::= { hmWanMbusD8 39 }

hmWanMbusD8VIF11		OBJECT-TYPE
			SYNTAX	INTEGER
			MAX-ACCESS	read-only
			STATUS	current
			::= { hmWanMbusD8 40 }

hmWanMbusD8Value11		OBJECT-TYPE
			SYNTAX	INTEGER
			MAX-ACCESS	read-only
			STATUS	current
			::= { hmWanMbusD8 41 }

hmWanMbusD8VIF12		OBJECT-TYPE
			SYNTAX	INTEGER
			MAX-ACCESS	read-only
			STATUS	current
			::= { hmWanMbusD8 42 }

hmWanMbusD8Value12		OBJECT-TYPE
			SYNTAX	INTEGER
			MAX-ACCESS	read-only
			STATUS	current
			::= { hmWanMbusD8 43 }

hmWanMbusD8VIF13		OBJECT-TYPE
			SYNTAX	INTEGER
			MAX-ACCESS	read-only
			STATUS	current
			::= { hmWanMbusD8 44 }

hmWanMbusD8Value13		OBJECT-TYPE
			SYNTAX	INTEGER
			MAX-ACCESS	read-only
			STATUS	current
			::= { hmWanMbusD8 45 }

hmWanMbusD8VIF14		OBJECT-TYPE
			SYNTAX	INTEGER
			MAX-ACCESS	read-only
			STATUS	current
			::= { hmWanMbusD8 46 }

hmWanMbusD8Value14		OBJECT-TYPE
			SYNTAX	INTEGER
			MAX-ACCESS	read-only
			STATUS	current
			::= { hmWanMbusD8 47 }

hmWanMbusD8VIF15		OBJECT-TYPE
			SYNTAX	INTEGER
			MAX-ACCESS	read-only
			STATUS	current
			::= { hmWanMbusD8 48 }

hmWanMbusD8Value15		OBJECT-TYPE
			SYNTAX	INTEGER
			MAX-ACCESS	read-only
			STATUS	current
			::= { hmWanMbusD8 49 }

hmWanMbusD8VIF16		OBJECT-TYPE
			SYNTAX	INTEGER
			MAX-ACCESS	read-only
			STATUS	current
			::= { hmWanMbusD8 50 }

hmWanMbusD8Value16		OBJECT-TYPE
			SYNTAX	INTEGER
			MAX-ACCESS	read-only
			STATUS	current
			::= { hmWanMbusD8 51 }

hmWanMbusD8VIF17		OBJECT-TYPE
			SYNTAX	INTEGER
			MAX-ACCESS	read-only
			STATUS	current
			::= { hmWanMbusD8 52 }

hmWanMbusD8Value17		OBJECT-TYPE
			SYNTAX	INTEGER
			MAX-ACCESS	read-only
			STATUS	current
			::= { hmWanMbusD8 53 }

hmWanMbusD8VIF18		OBJECT-TYPE
			SYNTAX	INTEGER
			MAX-ACCESS	read-only
			STATUS	current
			::= { hmWanMbusD8 54 }

hmWanMbusD8Value18		OBJECT-TYPE
			SYNTAX	INTEGER
			MAX-ACCESS	read-only
			STATUS	current
			::= { hmWanMbusD8 55 }

hmWanMbusD8VIF19		OBJECT-TYPE
			SYNTAX	INTEGER
			MAX-ACCESS	read-only
			STATUS	current
			::= { hmWanMbusD8 56 }

hmWanMbusD8Value19		OBJECT-TYPE
			SYNTAX	INTEGER
			MAX-ACCESS	read-only
			STATUS	current
			::= { hmWanMbusD8 57 }

hmWanMbusD8VIF1A		OBJECT-TYPE
			SYNTAX	INTEGER
			MAX-ACCESS	read-only
			STATUS	current
			::= { hmWanMbusD8 58 }

hmWanMbusD8Value1A		OBJECT-TYPE
			SYNTAX	INTEGER
			MAX-ACCESS	read-only
			STATUS	current
			::= { hmWanMbusD8 59 }

hmWanMbusD8VIF1B		OBJECT-TYPE
			SYNTAX	INTEGER
			MAX-ACCESS	read-only
			STATUS	current
			::= { hmWanMbusD8 60 }

hmWanMbusD8Value1B		OBJECT-TYPE
			SYNTAX	INTEGER
			MAX-ACCESS	read-only
			STATUS	current
			::= { hmWanMbusD8 61 }

hmWanMbusD8VIF1C		OBJECT-TYPE
			SYNTAX	INTEGER
			MAX-ACCESS	read-only
			STATUS	current
			::= { hmWanMbusD8 62 }

hmWanMbusD8Value1C		OBJECT-TYPE
			SYNTAX	INTEGER
			MAX-ACCESS	read-only
			STATUS	current
			::= { hmWanMbusD8 63 }

hmWanMbusD8VIF1D		OBJECT-TYPE
			SYNTAX	INTEGER
			MAX-ACCESS	read-only
			STATUS	current
			::= { hmWanMbusD8 64 }

hmWanMbusD8Value1D		OBJECT-TYPE
			SYNTAX	INTEGER
			MAX-ACCESS	read-only
			STATUS	current
			::= { hmWanMbusD8 65 }

hmWanMbusD8VIF1E		OBJECT-TYPE
			SYNTAX	INTEGER
			MAX-ACCESS	read-only
			STATUS	current
			::= { hmWanMbusD8 66 }

hmWanMbusD8Value1E		OBJECT-TYPE
			SYNTAX	INTEGER
			MAX-ACCESS	read-only
			STATUS	current
			::= { hmWanMbusD8 67 }

hmWanMbusD8VIF1F		OBJECT-TYPE
			SYNTAX	INTEGER
			MAX-ACCESS	read-only
			STATUS	current
			::= { hmWanMbusD8 68 }

hmWanMbusD8Value1F		OBJECT-TYPE
			SYNTAX	INTEGER
			MAX-ACCESS	read-only
			STATUS	current
			::= { hmWanMbusD8 69 }

hmWanMbusD8VIF20		OBJECT-TYPE
			SYNTAX	INTEGER
			MAX-ACCESS	read-only
			STATUS	current
			::= { hmWanMbusD8 70 }

hmWanMbusD8Value20		OBJECT-TYPE
			SYNTAX	INTEGER
			MAX-ACCESS	read-only
			STATUS	current
			::= { hmWanMbusD8 71 }

hmWanMbusD8VIF21		OBJECT-TYPE
			SYNTAX	INTEGER
			MAX-ACCESS	read-only
			STATUS	current
			::= { hmWanMbusD8 72 }

hmWanMbusD8Value21		OBJECT-TYPE
			SYNTAX	INTEGER
			MAX-ACCESS	read-only
			STATUS	current
			::= { hmWanMbusD8 73 }

hmWanMbusD8VIF22		OBJECT-TYPE
			SYNTAX	INTEGER
			MAX-ACCESS	read-only
			STATUS	current
			::= { hmWanMbusD8 74 }

hmWanMbusD8Value22		OBJECT-TYPE
			SYNTAX	INTEGER
			MAX-ACCESS	read-only
			STATUS	current
			::= { hmWanMbusD8 75 }

hmWanMbusD8VIF23		OBJECT-TYPE
			SYNTAX	INTEGER
			MAX-ACCESS	read-only
			STATUS	current
			::= { hmWanMbusD8 76 }

hmWanMbusD8Value23		OBJECT-TYPE
			SYNTAX	INTEGER
			MAX-ACCESS	read-only
			STATUS	current
			::= { hmWanMbusD8 77 }

hmWanMbusD8VIF24		OBJECT-TYPE
			SYNTAX	INTEGER
			MAX-ACCESS	read-only
			STATUS	current
			::= { hmWanMbusD8 78 }

hmWanMbusD8Value24		OBJECT-TYPE
			SYNTAX	INTEGER
			MAX-ACCESS	read-only
			STATUS	current
			::= { hmWanMbusD8 79 }

hmWanMbusD8VIF25		OBJECT-TYPE
			SYNTAX	INTEGER
			MAX-ACCESS	read-only
			STATUS	current
			::= { hmWanMbusD8 80 }

hmWanMbusD8Value25		OBJECT-TYPE
			SYNTAX	INTEGER
			MAX-ACCESS	read-only
			STATUS	current
			::= { hmWanMbusD8 81 }

hmWanMbusD8VIF26		OBJECT-TYPE
			SYNTAX	INTEGER
			MAX-ACCESS	read-only
			STATUS	current
			::= { hmWanMbusD8 82 }

hmWanMbusD8Value26		OBJECT-TYPE
			SYNTAX	INTEGER
			MAX-ACCESS	read-only
			STATUS	current
			::= { hmWanMbusD8 83 }

hmWanMbusD8VIF27		OBJECT-TYPE
			SYNTAX	INTEGER
			MAX-ACCESS	read-only
			STATUS	current
			::= { hmWanMbusD8 84 }

hmWanMbusD8Value27		OBJECT-TYPE
			SYNTAX	INTEGER
			MAX-ACCESS	read-only
			STATUS	current
			::= { hmWanMbusD8 85 }

hmWanMbusD8VIF28		OBJECT-TYPE
			SYNTAX	INTEGER
			MAX-ACCESS	read-only
			STATUS	current
			::= { hmWanMbusD8 86 }

hmWanMbusD8Value28		OBJECT-TYPE
			SYNTAX	INTEGER
			MAX-ACCESS	read-only
			STATUS	current
			::= { hmWanMbusD8 87 }

hmWanMbusD8VIF29		OBJECT-TYPE
			SYNTAX	INTEGER
			MAX-ACCESS	read-only
			STATUS	current
			::= { hmWanMbusD8 88 }

hmWanMbusD8Value29		OBJECT-TYPE
			SYNTAX	INTEGER
			MAX-ACCESS	read-only
			STATUS	current
			::= { hmWanMbusD8 89 }

hmWanMbusD8VIF2A		OBJECT-TYPE
			SYNTAX	INTEGER
			MAX-ACCESS	read-only
			STATUS	current
			::= { hmWanMbusD8 90 }

hmWanMbusD8Value2A		OBJECT-TYPE
			SYNTAX	INTEGER
			MAX-ACCESS	read-only
			STATUS	current
			::= { hmWanMbusD8 91 }

hmWanMbusD8VIF2B		OBJECT-TYPE
			SYNTAX	INTEGER
			MAX-ACCESS	read-only
			STATUS	current
			::= { hmWanMbusD8 92 }

hmWanMbusD8Value2B		OBJECT-TYPE
			SYNTAX	INTEGER
			MAX-ACCESS	read-only
			STATUS	current
			::= { hmWanMbusD8 93 }

hmWanMbusD8VIF2C		OBJECT-TYPE
			SYNTAX	INTEGER
			MAX-ACCESS	read-only
			STATUS	current
			::= { hmWanMbusD8 94 }

hmWanMbusD8Value2C		OBJECT-TYPE
			SYNTAX	INTEGER
			MAX-ACCESS	read-only
			STATUS	current
			::= { hmWanMbusD8 95 }

hmWanMbusD8VIF2D		OBJECT-TYPE
			SYNTAX	INTEGER
			MAX-ACCESS	read-only
			STATUS	current
			::= { hmWanMbusD8 96 }

hmWanMbusD8Value2D		OBJECT-TYPE
			SYNTAX	INTEGER
			MAX-ACCESS	read-only
			STATUS	current
			::= { hmWanMbusD8 97 }

hmWanMbusD8VIF2E		OBJECT-TYPE
			SYNTAX	INTEGER
			MAX-ACCESS	read-only
			STATUS	current
			::= { hmWanMbusD8 98 }

hmWanMbusD8Value2E		OBJECT-TYPE
			SYNTAX	INTEGER
			MAX-ACCESS	read-only
			STATUS	current
			::= { hmWanMbusD8 99 }

hmWanMbusD8VIF2F		OBJECT-TYPE
			SYNTAX	INTEGER
			MAX-ACCESS	read-only
			STATUS	current
			::= { hmWanMbusD8 100 }

hmWanMbusD8Value2F		OBJECT-TYPE
			SYNTAX	INTEGER
			MAX-ACCESS	read-only
			STATUS	current
			::= { hmWanMbusD8 101 }

hmWanMbusD9			OBJECT IDENTIFIER ::= { hmWanMbus 217 }

hmWanMbusD9IdNumber		OBJECT-TYPE
			SYNTAX	Gauge32
			MAX-ACCESS	read-only
			STATUS	current
			::= { hmWanMbusD9 1 }

hmWanMbusD9Manufacturer	OBJECT-TYPE
			SYNTAX	Gauge32
			MAX-ACCESS	read-only
			STATUS	current
			::= { hmWanMbusD9 2 }

hmWanMbusD9Version		OBJECT-TYPE
			SYNTAX	Gauge32
			MAX-ACCESS	read-only
			STATUS	current
			::= { hmWanMbusD9 3 }

hmWanMbusD9Medium		OBJECT-TYPE
			SYNTAX	Gauge32
			MAX-ACCESS	read-only
			STATUS	current
			::= { hmWanMbusD9 4 }

hmWanMbusD9Status		OBJECT-TYPE
			SYNTAX	Gauge32
			MAX-ACCESS	read-only
			STATUS	current
			::= { hmWanMbusD9 5 }

hmWanMbusD9VIF00		OBJECT-TYPE
			SYNTAX	INTEGER
			MAX-ACCESS	read-only
			STATUS	current
			::= { hmWanMbusD9 6 }

hmWanMbusD9Value00		OBJECT-TYPE
			SYNTAX	INTEGER
			MAX-ACCESS	read-only
			STATUS	current
			::= { hmWanMbusD9 7 }

hmWanMbusD9VIF01		OBJECT-TYPE
			SYNTAX	INTEGER
			MAX-ACCESS	read-only
			STATUS	current
			::= { hmWanMbusD9 8 }

hmWanMbusD9Value01		OBJECT-TYPE
			SYNTAX	INTEGER
			MAX-ACCESS	read-only
			STATUS	current
			::= { hmWanMbusD9 9 }

hmWanMbusD9VIF02		OBJECT-TYPE
			SYNTAX	INTEGER
			MAX-ACCESS	read-only
			STATUS	current
			::= { hmWanMbusD9 10 }

hmWanMbusD9Value02		OBJECT-TYPE
			SYNTAX	INTEGER
			MAX-ACCESS	read-only
			STATUS	current
			::= { hmWanMbusD9 11 }

hmWanMbusD9VIF03		OBJECT-TYPE
			SYNTAX	INTEGER
			MAX-ACCESS	read-only
			STATUS	current
			::= { hmWanMbusD9 12 }

hmWanMbusD9Value03		OBJECT-TYPE
			SYNTAX	INTEGER
			MAX-ACCESS	read-only
			STATUS	current
			::= { hmWanMbusD9 13 }

hmWanMbusD9VIF04		OBJECT-TYPE
			SYNTAX	INTEGER
			MAX-ACCESS	read-only
			STATUS	current
			::= { hmWanMbusD9 14 }

hmWanMbusD9Value04		OBJECT-TYPE
			SYNTAX	INTEGER
			MAX-ACCESS	read-only
			STATUS	current
			::= { hmWanMbusD9 15 }

hmWanMbusD9VIF05		OBJECT-TYPE
			SYNTAX	INTEGER
			MAX-ACCESS	read-only
			STATUS	current
			::= { hmWanMbusD9 16 }

hmWanMbusD9Value05		OBJECT-TYPE
			SYNTAX	INTEGER
			MAX-ACCESS	read-only
			STATUS	current
			::= { hmWanMbusD9 17 }

hmWanMbusD9VIF06		OBJECT-TYPE
			SYNTAX	INTEGER
			MAX-ACCESS	read-only
			STATUS	current
			::= { hmWanMbusD9 18 }

hmWanMbusD9Value06		OBJECT-TYPE
			SYNTAX	INTEGER
			MAX-ACCESS	read-only
			STATUS	current
			::= { hmWanMbusD9 19 }

hmWanMbusD9VIF07		OBJECT-TYPE
			SYNTAX	INTEGER
			MAX-ACCESS	read-only
			STATUS	current
			::= { hmWanMbusD9 20 }

hmWanMbusD9Value07		OBJECT-TYPE
			SYNTAX	INTEGER
			MAX-ACCESS	read-only
			STATUS	current
			::= { hmWanMbusD9 21 }

hmWanMbusD9VIF08		OBJECT-TYPE
			SYNTAX	INTEGER
			MAX-ACCESS	read-only
			STATUS	current
			::= { hmWanMbusD9 22 }

hmWanMbusD9Value08		OBJECT-TYPE
			SYNTAX	INTEGER
			MAX-ACCESS	read-only
			STATUS	current
			::= { hmWanMbusD9 23 }

hmWanMbusD9VIF09		OBJECT-TYPE
			SYNTAX	INTEGER
			MAX-ACCESS	read-only
			STATUS	current
			::= { hmWanMbusD9 24 }

hmWanMbusD9Value09		OBJECT-TYPE
			SYNTAX	INTEGER
			MAX-ACCESS	read-only
			STATUS	current
			::= { hmWanMbusD9 25 }

hmWanMbusD9VIF0A		OBJECT-TYPE
			SYNTAX	INTEGER
			MAX-ACCESS	read-only
			STATUS	current
			::= { hmWanMbusD9 26 }

hmWanMbusD9Value0A		OBJECT-TYPE
			SYNTAX	INTEGER
			MAX-ACCESS	read-only
			STATUS	current
			::= { hmWanMbusD9 27 }

hmWanMbusD9VIF0B		OBJECT-TYPE
			SYNTAX	INTEGER
			MAX-ACCESS	read-only
			STATUS	current
			::= { hmWanMbusD9 28 }

hmWanMbusD9Value0B		OBJECT-TYPE
			SYNTAX	INTEGER
			MAX-ACCESS	read-only
			STATUS	current
			::= { hmWanMbusD9 29 }

hmWanMbusD9VIF0C		OBJECT-TYPE
			SYNTAX	INTEGER
			MAX-ACCESS	read-only
			STATUS	current
			::= { hmWanMbusD9 30 }

hmWanMbusD9Value0C		OBJECT-TYPE
			SYNTAX	INTEGER
			MAX-ACCESS	read-only
			STATUS	current
			::= { hmWanMbusD9 31 }

hmWanMbusD9VIF0D		OBJECT-TYPE
			SYNTAX	INTEGER
			MAX-ACCESS	read-only
			STATUS	current
			::= { hmWanMbusD9 32 }

hmWanMbusD9Value0D		OBJECT-TYPE
			SYNTAX	INTEGER
			MAX-ACCESS	read-only
			STATUS	current
			::= { hmWanMbusD9 33 }

hmWanMbusD9VIF0E		OBJECT-TYPE
			SYNTAX	INTEGER
			MAX-ACCESS	read-only
			STATUS	current
			::= { hmWanMbusD9 34 }

hmWanMbusD9Value0E		OBJECT-TYPE
			SYNTAX	INTEGER
			MAX-ACCESS	read-only
			STATUS	current
			::= { hmWanMbusD9 35 }

hmWanMbusD9VIF0F		OBJECT-TYPE
			SYNTAX	INTEGER
			MAX-ACCESS	read-only
			STATUS	current
			::= { hmWanMbusD9 36 }

hmWanMbusD9Value0F		OBJECT-TYPE
			SYNTAX	INTEGER
			MAX-ACCESS	read-only
			STATUS	current
			::= { hmWanMbusD9 37 }

hmWanMbusD9VIF10		OBJECT-TYPE
			SYNTAX	INTEGER
			MAX-ACCESS	read-only
			STATUS	current
			::= { hmWanMbusD9 38 }

hmWanMbusD9Value10		OBJECT-TYPE
			SYNTAX	INTEGER
			MAX-ACCESS	read-only
			STATUS	current
			::= { hmWanMbusD9 39 }

hmWanMbusD9VIF11		OBJECT-TYPE
			SYNTAX	INTEGER
			MAX-ACCESS	read-only
			STATUS	current
			::= { hmWanMbusD9 40 }

hmWanMbusD9Value11		OBJECT-TYPE
			SYNTAX	INTEGER
			MAX-ACCESS	read-only
			STATUS	current
			::= { hmWanMbusD9 41 }

hmWanMbusD9VIF12		OBJECT-TYPE
			SYNTAX	INTEGER
			MAX-ACCESS	read-only
			STATUS	current
			::= { hmWanMbusD9 42 }

hmWanMbusD9Value12		OBJECT-TYPE
			SYNTAX	INTEGER
			MAX-ACCESS	read-only
			STATUS	current
			::= { hmWanMbusD9 43 }

hmWanMbusD9VIF13		OBJECT-TYPE
			SYNTAX	INTEGER
			MAX-ACCESS	read-only
			STATUS	current
			::= { hmWanMbusD9 44 }

hmWanMbusD9Value13		OBJECT-TYPE
			SYNTAX	INTEGER
			MAX-ACCESS	read-only
			STATUS	current
			::= { hmWanMbusD9 45 }

hmWanMbusD9VIF14		OBJECT-TYPE
			SYNTAX	INTEGER
			MAX-ACCESS	read-only
			STATUS	current
			::= { hmWanMbusD9 46 }

hmWanMbusD9Value14		OBJECT-TYPE
			SYNTAX	INTEGER
			MAX-ACCESS	read-only
			STATUS	current
			::= { hmWanMbusD9 47 }

hmWanMbusD9VIF15		OBJECT-TYPE
			SYNTAX	INTEGER
			MAX-ACCESS	read-only
			STATUS	current
			::= { hmWanMbusD9 48 }

hmWanMbusD9Value15		OBJECT-TYPE
			SYNTAX	INTEGER
			MAX-ACCESS	read-only
			STATUS	current
			::= { hmWanMbusD9 49 }

hmWanMbusD9VIF16		OBJECT-TYPE
			SYNTAX	INTEGER
			MAX-ACCESS	read-only
			STATUS	current
			::= { hmWanMbusD9 50 }

hmWanMbusD9Value16		OBJECT-TYPE
			SYNTAX	INTEGER
			MAX-ACCESS	read-only
			STATUS	current
			::= { hmWanMbusD9 51 }

hmWanMbusD9VIF17		OBJECT-TYPE
			SYNTAX	INTEGER
			MAX-ACCESS	read-only
			STATUS	current
			::= { hmWanMbusD9 52 }

hmWanMbusD9Value17		OBJECT-TYPE
			SYNTAX	INTEGER
			MAX-ACCESS	read-only
			STATUS	current
			::= { hmWanMbusD9 53 }

hmWanMbusD9VIF18		OBJECT-TYPE
			SYNTAX	INTEGER
			MAX-ACCESS	read-only
			STATUS	current
			::= { hmWanMbusD9 54 }

hmWanMbusD9Value18		OBJECT-TYPE
			SYNTAX	INTEGER
			MAX-ACCESS	read-only
			STATUS	current
			::= { hmWanMbusD9 55 }

hmWanMbusD9VIF19		OBJECT-TYPE
			SYNTAX	INTEGER
			MAX-ACCESS	read-only
			STATUS	current
			::= { hmWanMbusD9 56 }

hmWanMbusD9Value19		OBJECT-TYPE
			SYNTAX	INTEGER
			MAX-ACCESS	read-only
			STATUS	current
			::= { hmWanMbusD9 57 }

hmWanMbusD9VIF1A		OBJECT-TYPE
			SYNTAX	INTEGER
			MAX-ACCESS	read-only
			STATUS	current
			::= { hmWanMbusD9 58 }

hmWanMbusD9Value1A		OBJECT-TYPE
			SYNTAX	INTEGER
			MAX-ACCESS	read-only
			STATUS	current
			::= { hmWanMbusD9 59 }

hmWanMbusD9VIF1B		OBJECT-TYPE
			SYNTAX	INTEGER
			MAX-ACCESS	read-only
			STATUS	current
			::= { hmWanMbusD9 60 }

hmWanMbusD9Value1B		OBJECT-TYPE
			SYNTAX	INTEGER
			MAX-ACCESS	read-only
			STATUS	current
			::= { hmWanMbusD9 61 }

hmWanMbusD9VIF1C		OBJECT-TYPE
			SYNTAX	INTEGER
			MAX-ACCESS	read-only
			STATUS	current
			::= { hmWanMbusD9 62 }

hmWanMbusD9Value1C		OBJECT-TYPE
			SYNTAX	INTEGER
			MAX-ACCESS	read-only
			STATUS	current
			::= { hmWanMbusD9 63 }

hmWanMbusD9VIF1D		OBJECT-TYPE
			SYNTAX	INTEGER
			MAX-ACCESS	read-only
			STATUS	current
			::= { hmWanMbusD9 64 }

hmWanMbusD9Value1D		OBJECT-TYPE
			SYNTAX	INTEGER
			MAX-ACCESS	read-only
			STATUS	current
			::= { hmWanMbusD9 65 }

hmWanMbusD9VIF1E		OBJECT-TYPE
			SYNTAX	INTEGER
			MAX-ACCESS	read-only
			STATUS	current
			::= { hmWanMbusD9 66 }

hmWanMbusD9Value1E		OBJECT-TYPE
			SYNTAX	INTEGER
			MAX-ACCESS	read-only
			STATUS	current
			::= { hmWanMbusD9 67 }

hmWanMbusD9VIF1F		OBJECT-TYPE
			SYNTAX	INTEGER
			MAX-ACCESS	read-only
			STATUS	current
			::= { hmWanMbusD9 68 }

hmWanMbusD9Value1F		OBJECT-TYPE
			SYNTAX	INTEGER
			MAX-ACCESS	read-only
			STATUS	current
			::= { hmWanMbusD9 69 }

hmWanMbusD9VIF20		OBJECT-TYPE
			SYNTAX	INTEGER
			MAX-ACCESS	read-only
			STATUS	current
			::= { hmWanMbusD9 70 }

hmWanMbusD9Value20		OBJECT-TYPE
			SYNTAX	INTEGER
			MAX-ACCESS	read-only
			STATUS	current
			::= { hmWanMbusD9 71 }

hmWanMbusD9VIF21		OBJECT-TYPE
			SYNTAX	INTEGER
			MAX-ACCESS	read-only
			STATUS	current
			::= { hmWanMbusD9 72 }

hmWanMbusD9Value21		OBJECT-TYPE
			SYNTAX	INTEGER
			MAX-ACCESS	read-only
			STATUS	current
			::= { hmWanMbusD9 73 }

hmWanMbusD9VIF22		OBJECT-TYPE
			SYNTAX	INTEGER
			MAX-ACCESS	read-only
			STATUS	current
			::= { hmWanMbusD9 74 }

hmWanMbusD9Value22		OBJECT-TYPE
			SYNTAX	INTEGER
			MAX-ACCESS	read-only
			STATUS	current
			::= { hmWanMbusD9 75 }

hmWanMbusD9VIF23		OBJECT-TYPE
			SYNTAX	INTEGER
			MAX-ACCESS	read-only
			STATUS	current
			::= { hmWanMbusD9 76 }

hmWanMbusD9Value23		OBJECT-TYPE
			SYNTAX	INTEGER
			MAX-ACCESS	read-only
			STATUS	current
			::= { hmWanMbusD9 77 }

hmWanMbusD9VIF24		OBJECT-TYPE
			SYNTAX	INTEGER
			MAX-ACCESS	read-only
			STATUS	current
			::= { hmWanMbusD9 78 }

hmWanMbusD9Value24		OBJECT-TYPE
			SYNTAX	INTEGER
			MAX-ACCESS	read-only
			STATUS	current
			::= { hmWanMbusD9 79 }

hmWanMbusD9VIF25		OBJECT-TYPE
			SYNTAX	INTEGER
			MAX-ACCESS	read-only
			STATUS	current
			::= { hmWanMbusD9 80 }

hmWanMbusD9Value25		OBJECT-TYPE
			SYNTAX	INTEGER
			MAX-ACCESS	read-only
			STATUS	current
			::= { hmWanMbusD9 81 }

hmWanMbusD9VIF26		OBJECT-TYPE
			SYNTAX	INTEGER
			MAX-ACCESS	read-only
			STATUS	current
			::= { hmWanMbusD9 82 }

hmWanMbusD9Value26		OBJECT-TYPE
			SYNTAX	INTEGER
			MAX-ACCESS	read-only
			STATUS	current
			::= { hmWanMbusD9 83 }

hmWanMbusD9VIF27		OBJECT-TYPE
			SYNTAX	INTEGER
			MAX-ACCESS	read-only
			STATUS	current
			::= { hmWanMbusD9 84 }

hmWanMbusD9Value27		OBJECT-TYPE
			SYNTAX	INTEGER
			MAX-ACCESS	read-only
			STATUS	current
			::= { hmWanMbusD9 85 }

hmWanMbusD9VIF28		OBJECT-TYPE
			SYNTAX	INTEGER
			MAX-ACCESS	read-only
			STATUS	current
			::= { hmWanMbusD9 86 }

hmWanMbusD9Value28		OBJECT-TYPE
			SYNTAX	INTEGER
			MAX-ACCESS	read-only
			STATUS	current
			::= { hmWanMbusD9 87 }

hmWanMbusD9VIF29		OBJECT-TYPE
			SYNTAX	INTEGER
			MAX-ACCESS	read-only
			STATUS	current
			::= { hmWanMbusD9 88 }

hmWanMbusD9Value29		OBJECT-TYPE
			SYNTAX	INTEGER
			MAX-ACCESS	read-only
			STATUS	current
			::= { hmWanMbusD9 89 }

hmWanMbusD9VIF2A		OBJECT-TYPE
			SYNTAX	INTEGER
			MAX-ACCESS	read-only
			STATUS	current
			::= { hmWanMbusD9 90 }

hmWanMbusD9Value2A		OBJECT-TYPE
			SYNTAX	INTEGER
			MAX-ACCESS	read-only
			STATUS	current
			::= { hmWanMbusD9 91 }

hmWanMbusD9VIF2B		OBJECT-TYPE
			SYNTAX	INTEGER
			MAX-ACCESS	read-only
			STATUS	current
			::= { hmWanMbusD9 92 }

hmWanMbusD9Value2B		OBJECT-TYPE
			SYNTAX	INTEGER
			MAX-ACCESS	read-only
			STATUS	current
			::= { hmWanMbusD9 93 }

hmWanMbusD9VIF2C		OBJECT-TYPE
			SYNTAX	INTEGER
			MAX-ACCESS	read-only
			STATUS	current
			::= { hmWanMbusD9 94 }

hmWanMbusD9Value2C		OBJECT-TYPE
			SYNTAX	INTEGER
			MAX-ACCESS	read-only
			STATUS	current
			::= { hmWanMbusD9 95 }

hmWanMbusD9VIF2D		OBJECT-TYPE
			SYNTAX	INTEGER
			MAX-ACCESS	read-only
			STATUS	current
			::= { hmWanMbusD9 96 }

hmWanMbusD9Value2D		OBJECT-TYPE
			SYNTAX	INTEGER
			MAX-ACCESS	read-only
			STATUS	current
			::= { hmWanMbusD9 97 }

hmWanMbusD9VIF2E		OBJECT-TYPE
			SYNTAX	INTEGER
			MAX-ACCESS	read-only
			STATUS	current
			::= { hmWanMbusD9 98 }

hmWanMbusD9Value2E		OBJECT-TYPE
			SYNTAX	INTEGER
			MAX-ACCESS	read-only
			STATUS	current
			::= { hmWanMbusD9 99 }

hmWanMbusD9VIF2F		OBJECT-TYPE
			SYNTAX	INTEGER
			MAX-ACCESS	read-only
			STATUS	current
			::= { hmWanMbusD9 100 }

hmWanMbusD9Value2F		OBJECT-TYPE
			SYNTAX	INTEGER
			MAX-ACCESS	read-only
			STATUS	current
			::= { hmWanMbusD9 101 }

hmWanMbusDA			OBJECT IDENTIFIER ::= { hmWanMbus 218 }

hmWanMbusDAIdNumber		OBJECT-TYPE
			SYNTAX	Gauge32
			MAX-ACCESS	read-only
			STATUS	current
			::= { hmWanMbusDA 1 }

hmWanMbusDAManufacturer	OBJECT-TYPE
			SYNTAX	Gauge32
			MAX-ACCESS	read-only
			STATUS	current
			::= { hmWanMbusDA 2 }

hmWanMbusDAVersion		OBJECT-TYPE
			SYNTAX	Gauge32
			MAX-ACCESS	read-only
			STATUS	current
			::= { hmWanMbusDA 3 }

hmWanMbusDAMedium		OBJECT-TYPE
			SYNTAX	Gauge32
			MAX-ACCESS	read-only
			STATUS	current
			::= { hmWanMbusDA 4 }

hmWanMbusDAStatus		OBJECT-TYPE
			SYNTAX	Gauge32
			MAX-ACCESS	read-only
			STATUS	current
			::= { hmWanMbusDA 5 }

hmWanMbusDAVIF00		OBJECT-TYPE
			SYNTAX	INTEGER
			MAX-ACCESS	read-only
			STATUS	current
			::= { hmWanMbusDA 6 }

hmWanMbusDAValue00		OBJECT-TYPE
			SYNTAX	INTEGER
			MAX-ACCESS	read-only
			STATUS	current
			::= { hmWanMbusDA 7 }

hmWanMbusDAVIF01		OBJECT-TYPE
			SYNTAX	INTEGER
			MAX-ACCESS	read-only
			STATUS	current
			::= { hmWanMbusDA 8 }

hmWanMbusDAValue01		OBJECT-TYPE
			SYNTAX	INTEGER
			MAX-ACCESS	read-only
			STATUS	current
			::= { hmWanMbusDA 9 }

hmWanMbusDAVIF02		OBJECT-TYPE
			SYNTAX	INTEGER
			MAX-ACCESS	read-only
			STATUS	current
			::= { hmWanMbusDA 10 }

hmWanMbusDAValue02		OBJECT-TYPE
			SYNTAX	INTEGER
			MAX-ACCESS	read-only
			STATUS	current
			::= { hmWanMbusDA 11 }

hmWanMbusDAVIF03		OBJECT-TYPE
			SYNTAX	INTEGER
			MAX-ACCESS	read-only
			STATUS	current
			::= { hmWanMbusDA 12 }

hmWanMbusDAValue03		OBJECT-TYPE
			SYNTAX	INTEGER
			MAX-ACCESS	read-only
			STATUS	current
			::= { hmWanMbusDA 13 }

hmWanMbusDAVIF04		OBJECT-TYPE
			SYNTAX	INTEGER
			MAX-ACCESS	read-only
			STATUS	current
			::= { hmWanMbusDA 14 }

hmWanMbusDAValue04		OBJECT-TYPE
			SYNTAX	INTEGER
			MAX-ACCESS	read-only
			STATUS	current
			::= { hmWanMbusDA 15 }

hmWanMbusDAVIF05		OBJECT-TYPE
			SYNTAX	INTEGER
			MAX-ACCESS	read-only
			STATUS	current
			::= { hmWanMbusDA 16 }

hmWanMbusDAValue05		OBJECT-TYPE
			SYNTAX	INTEGER
			MAX-ACCESS	read-only
			STATUS	current
			::= { hmWanMbusDA 17 }

hmWanMbusDAVIF06		OBJECT-TYPE
			SYNTAX	INTEGER
			MAX-ACCESS	read-only
			STATUS	current
			::= { hmWanMbusDA 18 }

hmWanMbusDAValue06		OBJECT-TYPE
			SYNTAX	INTEGER
			MAX-ACCESS	read-only
			STATUS	current
			::= { hmWanMbusDA 19 }

hmWanMbusDAVIF07		OBJECT-TYPE
			SYNTAX	INTEGER
			MAX-ACCESS	read-only
			STATUS	current
			::= { hmWanMbusDA 20 }

hmWanMbusDAValue07		OBJECT-TYPE
			SYNTAX	INTEGER
			MAX-ACCESS	read-only
			STATUS	current
			::= { hmWanMbusDA 21 }

hmWanMbusDAVIF08		OBJECT-TYPE
			SYNTAX	INTEGER
			MAX-ACCESS	read-only
			STATUS	current
			::= { hmWanMbusDA 22 }

hmWanMbusDAValue08		OBJECT-TYPE
			SYNTAX	INTEGER
			MAX-ACCESS	read-only
			STATUS	current
			::= { hmWanMbusDA 23 }

hmWanMbusDAVIF09		OBJECT-TYPE
			SYNTAX	INTEGER
			MAX-ACCESS	read-only
			STATUS	current
			::= { hmWanMbusDA 24 }

hmWanMbusDAValue09		OBJECT-TYPE
			SYNTAX	INTEGER
			MAX-ACCESS	read-only
			STATUS	current
			::= { hmWanMbusDA 25 }

hmWanMbusDAVIF0A		OBJECT-TYPE
			SYNTAX	INTEGER
			MAX-ACCESS	read-only
			STATUS	current
			::= { hmWanMbusDA 26 }

hmWanMbusDAValue0A		OBJECT-TYPE
			SYNTAX	INTEGER
			MAX-ACCESS	read-only
			STATUS	current
			::= { hmWanMbusDA 27 }

hmWanMbusDAVIF0B		OBJECT-TYPE
			SYNTAX	INTEGER
			MAX-ACCESS	read-only
			STATUS	current
			::= { hmWanMbusDA 28 }

hmWanMbusDAValue0B		OBJECT-TYPE
			SYNTAX	INTEGER
			MAX-ACCESS	read-only
			STATUS	current
			::= { hmWanMbusDA 29 }

hmWanMbusDAVIF0C		OBJECT-TYPE
			SYNTAX	INTEGER
			MAX-ACCESS	read-only
			STATUS	current
			::= { hmWanMbusDA 30 }

hmWanMbusDAValue0C		OBJECT-TYPE
			SYNTAX	INTEGER
			MAX-ACCESS	read-only
			STATUS	current
			::= { hmWanMbusDA 31 }

hmWanMbusDAVIF0D		OBJECT-TYPE
			SYNTAX	INTEGER
			MAX-ACCESS	read-only
			STATUS	current
			::= { hmWanMbusDA 32 }

hmWanMbusDAValue0D		OBJECT-TYPE
			SYNTAX	INTEGER
			MAX-ACCESS	read-only
			STATUS	current
			::= { hmWanMbusDA 33 }

hmWanMbusDAVIF0E		OBJECT-TYPE
			SYNTAX	INTEGER
			MAX-ACCESS	read-only
			STATUS	current
			::= { hmWanMbusDA 34 }

hmWanMbusDAValue0E		OBJECT-TYPE
			SYNTAX	INTEGER
			MAX-ACCESS	read-only
			STATUS	current
			::= { hmWanMbusDA 35 }

hmWanMbusDAVIF0F		OBJECT-TYPE
			SYNTAX	INTEGER
			MAX-ACCESS	read-only
			STATUS	current
			::= { hmWanMbusDA 36 }

hmWanMbusDAValue0F		OBJECT-TYPE
			SYNTAX	INTEGER
			MAX-ACCESS	read-only
			STATUS	current
			::= { hmWanMbusDA 37 }

hmWanMbusDAVIF10		OBJECT-TYPE
			SYNTAX	INTEGER
			MAX-ACCESS	read-only
			STATUS	current
			::= { hmWanMbusDA 38 }

hmWanMbusDAValue10		OBJECT-TYPE
			SYNTAX	INTEGER
			MAX-ACCESS	read-only
			STATUS	current
			::= { hmWanMbusDA 39 }

hmWanMbusDAVIF11		OBJECT-TYPE
			SYNTAX	INTEGER
			MAX-ACCESS	read-only
			STATUS	current
			::= { hmWanMbusDA 40 }

hmWanMbusDAValue11		OBJECT-TYPE
			SYNTAX	INTEGER
			MAX-ACCESS	read-only
			STATUS	current
			::= { hmWanMbusDA 41 }

hmWanMbusDAVIF12		OBJECT-TYPE
			SYNTAX	INTEGER
			MAX-ACCESS	read-only
			STATUS	current
			::= { hmWanMbusDA 42 }

hmWanMbusDAValue12		OBJECT-TYPE
			SYNTAX	INTEGER
			MAX-ACCESS	read-only
			STATUS	current
			::= { hmWanMbusDA 43 }

hmWanMbusDAVIF13		OBJECT-TYPE
			SYNTAX	INTEGER
			MAX-ACCESS	read-only
			STATUS	current
			::= { hmWanMbusDA 44 }

hmWanMbusDAValue13		OBJECT-TYPE
			SYNTAX	INTEGER
			MAX-ACCESS	read-only
			STATUS	current
			::= { hmWanMbusDA 45 }

hmWanMbusDAVIF14		OBJECT-TYPE
			SYNTAX	INTEGER
			MAX-ACCESS	read-only
			STATUS	current
			::= { hmWanMbusDA 46 }

hmWanMbusDAValue14		OBJECT-TYPE
			SYNTAX	INTEGER
			MAX-ACCESS	read-only
			STATUS	current
			::= { hmWanMbusDA 47 }

hmWanMbusDAVIF15		OBJECT-TYPE
			SYNTAX	INTEGER
			MAX-ACCESS	read-only
			STATUS	current
			::= { hmWanMbusDA 48 }

hmWanMbusDAValue15		OBJECT-TYPE
			SYNTAX	INTEGER
			MAX-ACCESS	read-only
			STATUS	current
			::= { hmWanMbusDA 49 }

hmWanMbusDAVIF16		OBJECT-TYPE
			SYNTAX	INTEGER
			MAX-ACCESS	read-only
			STATUS	current
			::= { hmWanMbusDA 50 }

hmWanMbusDAValue16		OBJECT-TYPE
			SYNTAX	INTEGER
			MAX-ACCESS	read-only
			STATUS	current
			::= { hmWanMbusDA 51 }

hmWanMbusDAVIF17		OBJECT-TYPE
			SYNTAX	INTEGER
			MAX-ACCESS	read-only
			STATUS	current
			::= { hmWanMbusDA 52 }

hmWanMbusDAValue17		OBJECT-TYPE
			SYNTAX	INTEGER
			MAX-ACCESS	read-only
			STATUS	current
			::= { hmWanMbusDA 53 }

hmWanMbusDAVIF18		OBJECT-TYPE
			SYNTAX	INTEGER
			MAX-ACCESS	read-only
			STATUS	current
			::= { hmWanMbusDA 54 }

hmWanMbusDAValue18		OBJECT-TYPE
			SYNTAX	INTEGER
			MAX-ACCESS	read-only
			STATUS	current
			::= { hmWanMbusDA 55 }

hmWanMbusDAVIF19		OBJECT-TYPE
			SYNTAX	INTEGER
			MAX-ACCESS	read-only
			STATUS	current
			::= { hmWanMbusDA 56 }

hmWanMbusDAValue19		OBJECT-TYPE
			SYNTAX	INTEGER
			MAX-ACCESS	read-only
			STATUS	current
			::= { hmWanMbusDA 57 }

hmWanMbusDAVIF1A		OBJECT-TYPE
			SYNTAX	INTEGER
			MAX-ACCESS	read-only
			STATUS	current
			::= { hmWanMbusDA 58 }

hmWanMbusDAValue1A		OBJECT-TYPE
			SYNTAX	INTEGER
			MAX-ACCESS	read-only
			STATUS	current
			::= { hmWanMbusDA 59 }

hmWanMbusDAVIF1B		OBJECT-TYPE
			SYNTAX	INTEGER
			MAX-ACCESS	read-only
			STATUS	current
			::= { hmWanMbusDA 60 }

hmWanMbusDAValue1B		OBJECT-TYPE
			SYNTAX	INTEGER
			MAX-ACCESS	read-only
			STATUS	current
			::= { hmWanMbusDA 61 }

hmWanMbusDAVIF1C		OBJECT-TYPE
			SYNTAX	INTEGER
			MAX-ACCESS	read-only
			STATUS	current
			::= { hmWanMbusDA 62 }

hmWanMbusDAValue1C		OBJECT-TYPE
			SYNTAX	INTEGER
			MAX-ACCESS	read-only
			STATUS	current
			::= { hmWanMbusDA 63 }

hmWanMbusDAVIF1D		OBJECT-TYPE
			SYNTAX	INTEGER
			MAX-ACCESS	read-only
			STATUS	current
			::= { hmWanMbusDA 64 }

hmWanMbusDAValue1D		OBJECT-TYPE
			SYNTAX	INTEGER
			MAX-ACCESS	read-only
			STATUS	current
			::= { hmWanMbusDA 65 }

hmWanMbusDAVIF1E		OBJECT-TYPE
			SYNTAX	INTEGER
			MAX-ACCESS	read-only
			STATUS	current
			::= { hmWanMbusDA 66 }

hmWanMbusDAValue1E		OBJECT-TYPE
			SYNTAX	INTEGER
			MAX-ACCESS	read-only
			STATUS	current
			::= { hmWanMbusDA 67 }

hmWanMbusDAVIF1F		OBJECT-TYPE
			SYNTAX	INTEGER
			MAX-ACCESS	read-only
			STATUS	current
			::= { hmWanMbusDA 68 }

hmWanMbusDAValue1F		OBJECT-TYPE
			SYNTAX	INTEGER
			MAX-ACCESS	read-only
			STATUS	current
			::= { hmWanMbusDA 69 }

hmWanMbusDAVIF20		OBJECT-TYPE
			SYNTAX	INTEGER
			MAX-ACCESS	read-only
			STATUS	current
			::= { hmWanMbusDA 70 }

hmWanMbusDAValue20		OBJECT-TYPE
			SYNTAX	INTEGER
			MAX-ACCESS	read-only
			STATUS	current
			::= { hmWanMbusDA 71 }

hmWanMbusDAVIF21		OBJECT-TYPE
			SYNTAX	INTEGER
			MAX-ACCESS	read-only
			STATUS	current
			::= { hmWanMbusDA 72 }

hmWanMbusDAValue21		OBJECT-TYPE
			SYNTAX	INTEGER
			MAX-ACCESS	read-only
			STATUS	current
			::= { hmWanMbusDA 73 }

hmWanMbusDAVIF22		OBJECT-TYPE
			SYNTAX	INTEGER
			MAX-ACCESS	read-only
			STATUS	current
			::= { hmWanMbusDA 74 }

hmWanMbusDAValue22		OBJECT-TYPE
			SYNTAX	INTEGER
			MAX-ACCESS	read-only
			STATUS	current
			::= { hmWanMbusDA 75 }

hmWanMbusDAVIF23		OBJECT-TYPE
			SYNTAX	INTEGER
			MAX-ACCESS	read-only
			STATUS	current
			::= { hmWanMbusDA 76 }

hmWanMbusDAValue23		OBJECT-TYPE
			SYNTAX	INTEGER
			MAX-ACCESS	read-only
			STATUS	current
			::= { hmWanMbusDA 77 }

hmWanMbusDAVIF24		OBJECT-TYPE
			SYNTAX	INTEGER
			MAX-ACCESS	read-only
			STATUS	current
			::= { hmWanMbusDA 78 }

hmWanMbusDAValue24		OBJECT-TYPE
			SYNTAX	INTEGER
			MAX-ACCESS	read-only
			STATUS	current
			::= { hmWanMbusDA 79 }

hmWanMbusDAVIF25		OBJECT-TYPE
			SYNTAX	INTEGER
			MAX-ACCESS	read-only
			STATUS	current
			::= { hmWanMbusDA 80 }

hmWanMbusDAValue25		OBJECT-TYPE
			SYNTAX	INTEGER
			MAX-ACCESS	read-only
			STATUS	current
			::= { hmWanMbusDA 81 }

hmWanMbusDAVIF26		OBJECT-TYPE
			SYNTAX	INTEGER
			MAX-ACCESS	read-only
			STATUS	current
			::= { hmWanMbusDA 82 }

hmWanMbusDAValue26		OBJECT-TYPE
			SYNTAX	INTEGER
			MAX-ACCESS	read-only
			STATUS	current
			::= { hmWanMbusDA 83 }

hmWanMbusDAVIF27		OBJECT-TYPE
			SYNTAX	INTEGER
			MAX-ACCESS	read-only
			STATUS	current
			::= { hmWanMbusDA 84 }

hmWanMbusDAValue27		OBJECT-TYPE
			SYNTAX	INTEGER
			MAX-ACCESS	read-only
			STATUS	current
			::= { hmWanMbusDA 85 }

hmWanMbusDAVIF28		OBJECT-TYPE
			SYNTAX	INTEGER
			MAX-ACCESS	read-only
			STATUS	current
			::= { hmWanMbusDA 86 }

hmWanMbusDAValue28		OBJECT-TYPE
			SYNTAX	INTEGER
			MAX-ACCESS	read-only
			STATUS	current
			::= { hmWanMbusDA 87 }

hmWanMbusDAVIF29		OBJECT-TYPE
			SYNTAX	INTEGER
			MAX-ACCESS	read-only
			STATUS	current
			::= { hmWanMbusDA 88 }

hmWanMbusDAValue29		OBJECT-TYPE
			SYNTAX	INTEGER
			MAX-ACCESS	read-only
			STATUS	current
			::= { hmWanMbusDA 89 }

hmWanMbusDAVIF2A		OBJECT-TYPE
			SYNTAX	INTEGER
			MAX-ACCESS	read-only
			STATUS	current
			::= { hmWanMbusDA 90 }

hmWanMbusDAValue2A		OBJECT-TYPE
			SYNTAX	INTEGER
			MAX-ACCESS	read-only
			STATUS	current
			::= { hmWanMbusDA 91 }

hmWanMbusDAVIF2B		OBJECT-TYPE
			SYNTAX	INTEGER
			MAX-ACCESS	read-only
			STATUS	current
			::= { hmWanMbusDA 92 }

hmWanMbusDAValue2B		OBJECT-TYPE
			SYNTAX	INTEGER
			MAX-ACCESS	read-only
			STATUS	current
			::= { hmWanMbusDA 93 }

hmWanMbusDAVIF2C		OBJECT-TYPE
			SYNTAX	INTEGER
			MAX-ACCESS	read-only
			STATUS	current
			::= { hmWanMbusDA 94 }

hmWanMbusDAValue2C		OBJECT-TYPE
			SYNTAX	INTEGER
			MAX-ACCESS	read-only
			STATUS	current
			::= { hmWanMbusDA 95 }

hmWanMbusDAVIF2D		OBJECT-TYPE
			SYNTAX	INTEGER
			MAX-ACCESS	read-only
			STATUS	current
			::= { hmWanMbusDA 96 }

hmWanMbusDAValue2D		OBJECT-TYPE
			SYNTAX	INTEGER
			MAX-ACCESS	read-only
			STATUS	current
			::= { hmWanMbusDA 97 }

hmWanMbusDAVIF2E		OBJECT-TYPE
			SYNTAX	INTEGER
			MAX-ACCESS	read-only
			STATUS	current
			::= { hmWanMbusDA 98 }

hmWanMbusDAValue2E		OBJECT-TYPE
			SYNTAX	INTEGER
			MAX-ACCESS	read-only
			STATUS	current
			::= { hmWanMbusDA 99 }

hmWanMbusDAVIF2F		OBJECT-TYPE
			SYNTAX	INTEGER
			MAX-ACCESS	read-only
			STATUS	current
			::= { hmWanMbusDA 100 }

hmWanMbusDAValue2F		OBJECT-TYPE
			SYNTAX	INTEGER
			MAX-ACCESS	read-only
			STATUS	current
			::= { hmWanMbusDA 101 }

hmWanMbusDB			OBJECT IDENTIFIER ::= { hmWanMbus 219 }

hmWanMbusDBIdNumber		OBJECT-TYPE
			SYNTAX	Gauge32
			MAX-ACCESS	read-only
			STATUS	current
			::= { hmWanMbusDB 1 }

hmWanMbusDBManufacturer	OBJECT-TYPE
			SYNTAX	Gauge32
			MAX-ACCESS	read-only
			STATUS	current
			::= { hmWanMbusDB 2 }

hmWanMbusDBVersion		OBJECT-TYPE
			SYNTAX	Gauge32
			MAX-ACCESS	read-only
			STATUS	current
			::= { hmWanMbusDB 3 }

hmWanMbusDBMedium		OBJECT-TYPE
			SYNTAX	Gauge32
			MAX-ACCESS	read-only
			STATUS	current
			::= { hmWanMbusDB 4 }

hmWanMbusDBStatus		OBJECT-TYPE
			SYNTAX	Gauge32
			MAX-ACCESS	read-only
			STATUS	current
			::= { hmWanMbusDB 5 }

hmWanMbusDBVIF00		OBJECT-TYPE
			SYNTAX	INTEGER
			MAX-ACCESS	read-only
			STATUS	current
			::= { hmWanMbusDB 6 }

hmWanMbusDBValue00		OBJECT-TYPE
			SYNTAX	INTEGER
			MAX-ACCESS	read-only
			STATUS	current
			::= { hmWanMbusDB 7 }

hmWanMbusDBVIF01		OBJECT-TYPE
			SYNTAX	INTEGER
			MAX-ACCESS	read-only
			STATUS	current
			::= { hmWanMbusDB 8 }

hmWanMbusDBValue01		OBJECT-TYPE
			SYNTAX	INTEGER
			MAX-ACCESS	read-only
			STATUS	current
			::= { hmWanMbusDB 9 }

hmWanMbusDBVIF02		OBJECT-TYPE
			SYNTAX	INTEGER
			MAX-ACCESS	read-only
			STATUS	current
			::= { hmWanMbusDB 10 }

hmWanMbusDBValue02		OBJECT-TYPE
			SYNTAX	INTEGER
			MAX-ACCESS	read-only
			STATUS	current
			::= { hmWanMbusDB 11 }

hmWanMbusDBVIF03		OBJECT-TYPE
			SYNTAX	INTEGER
			MAX-ACCESS	read-only
			STATUS	current
			::= { hmWanMbusDB 12 }

hmWanMbusDBValue03		OBJECT-TYPE
			SYNTAX	INTEGER
			MAX-ACCESS	read-only
			STATUS	current
			::= { hmWanMbusDB 13 }

hmWanMbusDBVIF04		OBJECT-TYPE
			SYNTAX	INTEGER
			MAX-ACCESS	read-only
			STATUS	current
			::= { hmWanMbusDB 14 }

hmWanMbusDBValue04		OBJECT-TYPE
			SYNTAX	INTEGER
			MAX-ACCESS	read-only
			STATUS	current
			::= { hmWanMbusDB 15 }

hmWanMbusDBVIF05		OBJECT-TYPE
			SYNTAX	INTEGER
			MAX-ACCESS	read-only
			STATUS	current
			::= { hmWanMbusDB 16 }

hmWanMbusDBValue05		OBJECT-TYPE
			SYNTAX	INTEGER
			MAX-ACCESS	read-only
			STATUS	current
			::= { hmWanMbusDB 17 }

hmWanMbusDBVIF06		OBJECT-TYPE
			SYNTAX	INTEGER
			MAX-ACCESS	read-only
			STATUS	current
			::= { hmWanMbusDB 18 }

hmWanMbusDBValue06		OBJECT-TYPE
			SYNTAX	INTEGER
			MAX-ACCESS	read-only
			STATUS	current
			::= { hmWanMbusDB 19 }

hmWanMbusDBVIF07		OBJECT-TYPE
			SYNTAX	INTEGER
			MAX-ACCESS	read-only
			STATUS	current
			::= { hmWanMbusDB 20 }

hmWanMbusDBValue07		OBJECT-TYPE
			SYNTAX	INTEGER
			MAX-ACCESS	read-only
			STATUS	current
			::= { hmWanMbusDB 21 }

hmWanMbusDBVIF08		OBJECT-TYPE
			SYNTAX	INTEGER
			MAX-ACCESS	read-only
			STATUS	current
			::= { hmWanMbusDB 22 }

hmWanMbusDBValue08		OBJECT-TYPE
			SYNTAX	INTEGER
			MAX-ACCESS	read-only
			STATUS	current
			::= { hmWanMbusDB 23 }

hmWanMbusDBVIF09		OBJECT-TYPE
			SYNTAX	INTEGER
			MAX-ACCESS	read-only
			STATUS	current
			::= { hmWanMbusDB 24 }

hmWanMbusDBValue09		OBJECT-TYPE
			SYNTAX	INTEGER
			MAX-ACCESS	read-only
			STATUS	current
			::= { hmWanMbusDB 25 }

hmWanMbusDBVIF0A		OBJECT-TYPE
			SYNTAX	INTEGER
			MAX-ACCESS	read-only
			STATUS	current
			::= { hmWanMbusDB 26 }

hmWanMbusDBValue0A		OBJECT-TYPE
			SYNTAX	INTEGER
			MAX-ACCESS	read-only
			STATUS	current
			::= { hmWanMbusDB 27 }

hmWanMbusDBVIF0B		OBJECT-TYPE
			SYNTAX	INTEGER
			MAX-ACCESS	read-only
			STATUS	current
			::= { hmWanMbusDB 28 }

hmWanMbusDBValue0B		OBJECT-TYPE
			SYNTAX	INTEGER
			MAX-ACCESS	read-only
			STATUS	current
			::= { hmWanMbusDB 29 }

hmWanMbusDBVIF0C		OBJECT-TYPE
			SYNTAX	INTEGER
			MAX-ACCESS	read-only
			STATUS	current
			::= { hmWanMbusDB 30 }

hmWanMbusDBValue0C		OBJECT-TYPE
			SYNTAX	INTEGER
			MAX-ACCESS	read-only
			STATUS	current
			::= { hmWanMbusDB 31 }

hmWanMbusDBVIF0D		OBJECT-TYPE
			SYNTAX	INTEGER
			MAX-ACCESS	read-only
			STATUS	current
			::= { hmWanMbusDB 32 }

hmWanMbusDBValue0D		OBJECT-TYPE
			SYNTAX	INTEGER
			MAX-ACCESS	read-only
			STATUS	current
			::= { hmWanMbusDB 33 }

hmWanMbusDBVIF0E		OBJECT-TYPE
			SYNTAX	INTEGER
			MAX-ACCESS	read-only
			STATUS	current
			::= { hmWanMbusDB 34 }

hmWanMbusDBValue0E		OBJECT-TYPE
			SYNTAX	INTEGER
			MAX-ACCESS	read-only
			STATUS	current
			::= { hmWanMbusDB 35 }

hmWanMbusDBVIF0F		OBJECT-TYPE
			SYNTAX	INTEGER
			MAX-ACCESS	read-only
			STATUS	current
			::= { hmWanMbusDB 36 }

hmWanMbusDBValue0F		OBJECT-TYPE
			SYNTAX	INTEGER
			MAX-ACCESS	read-only
			STATUS	current
			::= { hmWanMbusDB 37 }

hmWanMbusDBVIF10		OBJECT-TYPE
			SYNTAX	INTEGER
			MAX-ACCESS	read-only
			STATUS	current
			::= { hmWanMbusDB 38 }

hmWanMbusDBValue10		OBJECT-TYPE
			SYNTAX	INTEGER
			MAX-ACCESS	read-only
			STATUS	current
			::= { hmWanMbusDB 39 }

hmWanMbusDBVIF11		OBJECT-TYPE
			SYNTAX	INTEGER
			MAX-ACCESS	read-only
			STATUS	current
			::= { hmWanMbusDB 40 }

hmWanMbusDBValue11		OBJECT-TYPE
			SYNTAX	INTEGER
			MAX-ACCESS	read-only
			STATUS	current
			::= { hmWanMbusDB 41 }

hmWanMbusDBVIF12		OBJECT-TYPE
			SYNTAX	INTEGER
			MAX-ACCESS	read-only
			STATUS	current
			::= { hmWanMbusDB 42 }

hmWanMbusDBValue12		OBJECT-TYPE
			SYNTAX	INTEGER
			MAX-ACCESS	read-only
			STATUS	current
			::= { hmWanMbusDB 43 }

hmWanMbusDBVIF13		OBJECT-TYPE
			SYNTAX	INTEGER
			MAX-ACCESS	read-only
			STATUS	current
			::= { hmWanMbusDB 44 }

hmWanMbusDBValue13		OBJECT-TYPE
			SYNTAX	INTEGER
			MAX-ACCESS	read-only
			STATUS	current
			::= { hmWanMbusDB 45 }

hmWanMbusDBVIF14		OBJECT-TYPE
			SYNTAX	INTEGER
			MAX-ACCESS	read-only
			STATUS	current
			::= { hmWanMbusDB 46 }

hmWanMbusDBValue14		OBJECT-TYPE
			SYNTAX	INTEGER
			MAX-ACCESS	read-only
			STATUS	current
			::= { hmWanMbusDB 47 }

hmWanMbusDBVIF15		OBJECT-TYPE
			SYNTAX	INTEGER
			MAX-ACCESS	read-only
			STATUS	current
			::= { hmWanMbusDB 48 }

hmWanMbusDBValue15		OBJECT-TYPE
			SYNTAX	INTEGER
			MAX-ACCESS	read-only
			STATUS	current
			::= { hmWanMbusDB 49 }

hmWanMbusDBVIF16		OBJECT-TYPE
			SYNTAX	INTEGER
			MAX-ACCESS	read-only
			STATUS	current
			::= { hmWanMbusDB 50 }

hmWanMbusDBValue16		OBJECT-TYPE
			SYNTAX	INTEGER
			MAX-ACCESS	read-only
			STATUS	current
			::= { hmWanMbusDB 51 }

hmWanMbusDBVIF17		OBJECT-TYPE
			SYNTAX	INTEGER
			MAX-ACCESS	read-only
			STATUS	current
			::= { hmWanMbusDB 52 }

hmWanMbusDBValue17		OBJECT-TYPE
			SYNTAX	INTEGER
			MAX-ACCESS	read-only
			STATUS	current
			::= { hmWanMbusDB 53 }

hmWanMbusDBVIF18		OBJECT-TYPE
			SYNTAX	INTEGER
			MAX-ACCESS	read-only
			STATUS	current
			::= { hmWanMbusDB 54 }

hmWanMbusDBValue18		OBJECT-TYPE
			SYNTAX	INTEGER
			MAX-ACCESS	read-only
			STATUS	current
			::= { hmWanMbusDB 55 }

hmWanMbusDBVIF19		OBJECT-TYPE
			SYNTAX	INTEGER
			MAX-ACCESS	read-only
			STATUS	current
			::= { hmWanMbusDB 56 }

hmWanMbusDBValue19		OBJECT-TYPE
			SYNTAX	INTEGER
			MAX-ACCESS	read-only
			STATUS	current
			::= { hmWanMbusDB 57 }

hmWanMbusDBVIF1A		OBJECT-TYPE
			SYNTAX	INTEGER
			MAX-ACCESS	read-only
			STATUS	current
			::= { hmWanMbusDB 58 }

hmWanMbusDBValue1A		OBJECT-TYPE
			SYNTAX	INTEGER
			MAX-ACCESS	read-only
			STATUS	current
			::= { hmWanMbusDB 59 }

hmWanMbusDBVIF1B		OBJECT-TYPE
			SYNTAX	INTEGER
			MAX-ACCESS	read-only
			STATUS	current
			::= { hmWanMbusDB 60 }

hmWanMbusDBValue1B		OBJECT-TYPE
			SYNTAX	INTEGER
			MAX-ACCESS	read-only
			STATUS	current
			::= { hmWanMbusDB 61 }

hmWanMbusDBVIF1C		OBJECT-TYPE
			SYNTAX	INTEGER
			MAX-ACCESS	read-only
			STATUS	current
			::= { hmWanMbusDB 62 }

hmWanMbusDBValue1C		OBJECT-TYPE
			SYNTAX	INTEGER
			MAX-ACCESS	read-only
			STATUS	current
			::= { hmWanMbusDB 63 }

hmWanMbusDBVIF1D		OBJECT-TYPE
			SYNTAX	INTEGER
			MAX-ACCESS	read-only
			STATUS	current
			::= { hmWanMbusDB 64 }

hmWanMbusDBValue1D		OBJECT-TYPE
			SYNTAX	INTEGER
			MAX-ACCESS	read-only
			STATUS	current
			::= { hmWanMbusDB 65 }

hmWanMbusDBVIF1E		OBJECT-TYPE
			SYNTAX	INTEGER
			MAX-ACCESS	read-only
			STATUS	current
			::= { hmWanMbusDB 66 }

hmWanMbusDBValue1E		OBJECT-TYPE
			SYNTAX	INTEGER
			MAX-ACCESS	read-only
			STATUS	current
			::= { hmWanMbusDB 67 }

hmWanMbusDBVIF1F		OBJECT-TYPE
			SYNTAX	INTEGER
			MAX-ACCESS	read-only
			STATUS	current
			::= { hmWanMbusDB 68 }

hmWanMbusDBValue1F		OBJECT-TYPE
			SYNTAX	INTEGER
			MAX-ACCESS	read-only
			STATUS	current
			::= { hmWanMbusDB 69 }

hmWanMbusDBVIF20		OBJECT-TYPE
			SYNTAX	INTEGER
			MAX-ACCESS	read-only
			STATUS	current
			::= { hmWanMbusDB 70 }

hmWanMbusDBValue20		OBJECT-TYPE
			SYNTAX	INTEGER
			MAX-ACCESS	read-only
			STATUS	current
			::= { hmWanMbusDB 71 }

hmWanMbusDBVIF21		OBJECT-TYPE
			SYNTAX	INTEGER
			MAX-ACCESS	read-only
			STATUS	current
			::= { hmWanMbusDB 72 }

hmWanMbusDBValue21		OBJECT-TYPE
			SYNTAX	INTEGER
			MAX-ACCESS	read-only
			STATUS	current
			::= { hmWanMbusDB 73 }

hmWanMbusDBVIF22		OBJECT-TYPE
			SYNTAX	INTEGER
			MAX-ACCESS	read-only
			STATUS	current
			::= { hmWanMbusDB 74 }

hmWanMbusDBValue22		OBJECT-TYPE
			SYNTAX	INTEGER
			MAX-ACCESS	read-only
			STATUS	current
			::= { hmWanMbusDB 75 }

hmWanMbusDBVIF23		OBJECT-TYPE
			SYNTAX	INTEGER
			MAX-ACCESS	read-only
			STATUS	current
			::= { hmWanMbusDB 76 }

hmWanMbusDBValue23		OBJECT-TYPE
			SYNTAX	INTEGER
			MAX-ACCESS	read-only
			STATUS	current
			::= { hmWanMbusDB 77 }

hmWanMbusDBVIF24		OBJECT-TYPE
			SYNTAX	INTEGER
			MAX-ACCESS	read-only
			STATUS	current
			::= { hmWanMbusDB 78 }

hmWanMbusDBValue24		OBJECT-TYPE
			SYNTAX	INTEGER
			MAX-ACCESS	read-only
			STATUS	current
			::= { hmWanMbusDB 79 }

hmWanMbusDBVIF25		OBJECT-TYPE
			SYNTAX	INTEGER
			MAX-ACCESS	read-only
			STATUS	current
			::= { hmWanMbusDB 80 }

hmWanMbusDBValue25		OBJECT-TYPE
			SYNTAX	INTEGER
			MAX-ACCESS	read-only
			STATUS	current
			::= { hmWanMbusDB 81 }

hmWanMbusDBVIF26		OBJECT-TYPE
			SYNTAX	INTEGER
			MAX-ACCESS	read-only
			STATUS	current
			::= { hmWanMbusDB 82 }

hmWanMbusDBValue26		OBJECT-TYPE
			SYNTAX	INTEGER
			MAX-ACCESS	read-only
			STATUS	current
			::= { hmWanMbusDB 83 }

hmWanMbusDBVIF27		OBJECT-TYPE
			SYNTAX	INTEGER
			MAX-ACCESS	read-only
			STATUS	current
			::= { hmWanMbusDB 84 }

hmWanMbusDBValue27		OBJECT-TYPE
			SYNTAX	INTEGER
			MAX-ACCESS	read-only
			STATUS	current
			::= { hmWanMbusDB 85 }

hmWanMbusDBVIF28		OBJECT-TYPE
			SYNTAX	INTEGER
			MAX-ACCESS	read-only
			STATUS	current
			::= { hmWanMbusDB 86 }

hmWanMbusDBValue28		OBJECT-TYPE
			SYNTAX	INTEGER
			MAX-ACCESS	read-only
			STATUS	current
			::= { hmWanMbusDB 87 }

hmWanMbusDBVIF29		OBJECT-TYPE
			SYNTAX	INTEGER
			MAX-ACCESS	read-only
			STATUS	current
			::= { hmWanMbusDB 88 }

hmWanMbusDBValue29		OBJECT-TYPE
			SYNTAX	INTEGER
			MAX-ACCESS	read-only
			STATUS	current
			::= { hmWanMbusDB 89 }

hmWanMbusDBVIF2A		OBJECT-TYPE
			SYNTAX	INTEGER
			MAX-ACCESS	read-only
			STATUS	current
			::= { hmWanMbusDB 90 }

hmWanMbusDBValue2A		OBJECT-TYPE
			SYNTAX	INTEGER
			MAX-ACCESS	read-only
			STATUS	current
			::= { hmWanMbusDB 91 }

hmWanMbusDBVIF2B		OBJECT-TYPE
			SYNTAX	INTEGER
			MAX-ACCESS	read-only
			STATUS	current
			::= { hmWanMbusDB 92 }

hmWanMbusDBValue2B		OBJECT-TYPE
			SYNTAX	INTEGER
			MAX-ACCESS	read-only
			STATUS	current
			::= { hmWanMbusDB 93 }

hmWanMbusDBVIF2C		OBJECT-TYPE
			SYNTAX	INTEGER
			MAX-ACCESS	read-only
			STATUS	current
			::= { hmWanMbusDB 94 }

hmWanMbusDBValue2C		OBJECT-TYPE
			SYNTAX	INTEGER
			MAX-ACCESS	read-only
			STATUS	current
			::= { hmWanMbusDB 95 }

hmWanMbusDBVIF2D		OBJECT-TYPE
			SYNTAX	INTEGER
			MAX-ACCESS	read-only
			STATUS	current
			::= { hmWanMbusDB 96 }

hmWanMbusDBValue2D		OBJECT-TYPE
			SYNTAX	INTEGER
			MAX-ACCESS	read-only
			STATUS	current
			::= { hmWanMbusDB 97 }

hmWanMbusDBVIF2E		OBJECT-TYPE
			SYNTAX	INTEGER
			MAX-ACCESS	read-only
			STATUS	current
			::= { hmWanMbusDB 98 }

hmWanMbusDBValue2E		OBJECT-TYPE
			SYNTAX	INTEGER
			MAX-ACCESS	read-only
			STATUS	current
			::= { hmWanMbusDB 99 }

hmWanMbusDBVIF2F		OBJECT-TYPE
			SYNTAX	INTEGER
			MAX-ACCESS	read-only
			STATUS	current
			::= { hmWanMbusDB 100 }

hmWanMbusDBValue2F		OBJECT-TYPE
			SYNTAX	INTEGER
			MAX-ACCESS	read-only
			STATUS	current
			::= { hmWanMbusDB 101 }

hmWanMbusDC			OBJECT IDENTIFIER ::= { hmWanMbus 220 }

hmWanMbusDCIdNumber		OBJECT-TYPE
			SYNTAX	Gauge32
			MAX-ACCESS	read-only
			STATUS	current
			::= { hmWanMbusDC 1 }

hmWanMbusDCManufacturer	OBJECT-TYPE
			SYNTAX	Gauge32
			MAX-ACCESS	read-only
			STATUS	current
			::= { hmWanMbusDC 2 }

hmWanMbusDCVersion		OBJECT-TYPE
			SYNTAX	Gauge32
			MAX-ACCESS	read-only
			STATUS	current
			::= { hmWanMbusDC 3 }

hmWanMbusDCMedium		OBJECT-TYPE
			SYNTAX	Gauge32
			MAX-ACCESS	read-only
			STATUS	current
			::= { hmWanMbusDC 4 }

hmWanMbusDCStatus		OBJECT-TYPE
			SYNTAX	Gauge32
			MAX-ACCESS	read-only
			STATUS	current
			::= { hmWanMbusDC 5 }

hmWanMbusDCVIF00		OBJECT-TYPE
			SYNTAX	INTEGER
			MAX-ACCESS	read-only
			STATUS	current
			::= { hmWanMbusDC 6 }

hmWanMbusDCValue00		OBJECT-TYPE
			SYNTAX	INTEGER
			MAX-ACCESS	read-only
			STATUS	current
			::= { hmWanMbusDC 7 }

hmWanMbusDCVIF01		OBJECT-TYPE
			SYNTAX	INTEGER
			MAX-ACCESS	read-only
			STATUS	current
			::= { hmWanMbusDC 8 }

hmWanMbusDCValue01		OBJECT-TYPE
			SYNTAX	INTEGER
			MAX-ACCESS	read-only
			STATUS	current
			::= { hmWanMbusDC 9 }

hmWanMbusDCVIF02		OBJECT-TYPE
			SYNTAX	INTEGER
			MAX-ACCESS	read-only
			STATUS	current
			::= { hmWanMbusDC 10 }

hmWanMbusDCValue02		OBJECT-TYPE
			SYNTAX	INTEGER
			MAX-ACCESS	read-only
			STATUS	current
			::= { hmWanMbusDC 11 }

hmWanMbusDCVIF03		OBJECT-TYPE
			SYNTAX	INTEGER
			MAX-ACCESS	read-only
			STATUS	current
			::= { hmWanMbusDC 12 }

hmWanMbusDCValue03		OBJECT-TYPE
			SYNTAX	INTEGER
			MAX-ACCESS	read-only
			STATUS	current
			::= { hmWanMbusDC 13 }

hmWanMbusDCVIF04		OBJECT-TYPE
			SYNTAX	INTEGER
			MAX-ACCESS	read-only
			STATUS	current
			::= { hmWanMbusDC 14 }

hmWanMbusDCValue04		OBJECT-TYPE
			SYNTAX	INTEGER
			MAX-ACCESS	read-only
			STATUS	current
			::= { hmWanMbusDC 15 }

hmWanMbusDCVIF05		OBJECT-TYPE
			SYNTAX	INTEGER
			MAX-ACCESS	read-only
			STATUS	current
			::= { hmWanMbusDC 16 }

hmWanMbusDCValue05		OBJECT-TYPE
			SYNTAX	INTEGER
			MAX-ACCESS	read-only
			STATUS	current
			::= { hmWanMbusDC 17 }

hmWanMbusDCVIF06		OBJECT-TYPE
			SYNTAX	INTEGER
			MAX-ACCESS	read-only
			STATUS	current
			::= { hmWanMbusDC 18 }

hmWanMbusDCValue06		OBJECT-TYPE
			SYNTAX	INTEGER
			MAX-ACCESS	read-only
			STATUS	current
			::= { hmWanMbusDC 19 }

hmWanMbusDCVIF07		OBJECT-TYPE
			SYNTAX	INTEGER
			MAX-ACCESS	read-only
			STATUS	current
			::= { hmWanMbusDC 20 }

hmWanMbusDCValue07		OBJECT-TYPE
			SYNTAX	INTEGER
			MAX-ACCESS	read-only
			STATUS	current
			::= { hmWanMbusDC 21 }

hmWanMbusDCVIF08		OBJECT-TYPE
			SYNTAX	INTEGER
			MAX-ACCESS	read-only
			STATUS	current
			::= { hmWanMbusDC 22 }

hmWanMbusDCValue08		OBJECT-TYPE
			SYNTAX	INTEGER
			MAX-ACCESS	read-only
			STATUS	current
			::= { hmWanMbusDC 23 }

hmWanMbusDCVIF09		OBJECT-TYPE
			SYNTAX	INTEGER
			MAX-ACCESS	read-only
			STATUS	current
			::= { hmWanMbusDC 24 }

hmWanMbusDCValue09		OBJECT-TYPE
			SYNTAX	INTEGER
			MAX-ACCESS	read-only
			STATUS	current
			::= { hmWanMbusDC 25 }

hmWanMbusDCVIF0A		OBJECT-TYPE
			SYNTAX	INTEGER
			MAX-ACCESS	read-only
			STATUS	current
			::= { hmWanMbusDC 26 }

hmWanMbusDCValue0A		OBJECT-TYPE
			SYNTAX	INTEGER
			MAX-ACCESS	read-only
			STATUS	current
			::= { hmWanMbusDC 27 }

hmWanMbusDCVIF0B		OBJECT-TYPE
			SYNTAX	INTEGER
			MAX-ACCESS	read-only
			STATUS	current
			::= { hmWanMbusDC 28 }

hmWanMbusDCValue0B		OBJECT-TYPE
			SYNTAX	INTEGER
			MAX-ACCESS	read-only
			STATUS	current
			::= { hmWanMbusDC 29 }

hmWanMbusDCVIF0C		OBJECT-TYPE
			SYNTAX	INTEGER
			MAX-ACCESS	read-only
			STATUS	current
			::= { hmWanMbusDC 30 }

hmWanMbusDCValue0C		OBJECT-TYPE
			SYNTAX	INTEGER
			MAX-ACCESS	read-only
			STATUS	current
			::= { hmWanMbusDC 31 }

hmWanMbusDCVIF0D		OBJECT-TYPE
			SYNTAX	INTEGER
			MAX-ACCESS	read-only
			STATUS	current
			::= { hmWanMbusDC 32 }

hmWanMbusDCValue0D		OBJECT-TYPE
			SYNTAX	INTEGER
			MAX-ACCESS	read-only
			STATUS	current
			::= { hmWanMbusDC 33 }

hmWanMbusDCVIF0E		OBJECT-TYPE
			SYNTAX	INTEGER
			MAX-ACCESS	read-only
			STATUS	current
			::= { hmWanMbusDC 34 }

hmWanMbusDCValue0E		OBJECT-TYPE
			SYNTAX	INTEGER
			MAX-ACCESS	read-only
			STATUS	current
			::= { hmWanMbusDC 35 }

hmWanMbusDCVIF0F		OBJECT-TYPE
			SYNTAX	INTEGER
			MAX-ACCESS	read-only
			STATUS	current
			::= { hmWanMbusDC 36 }

hmWanMbusDCValue0F		OBJECT-TYPE
			SYNTAX	INTEGER
			MAX-ACCESS	read-only
			STATUS	current
			::= { hmWanMbusDC 37 }

hmWanMbusDCVIF10		OBJECT-TYPE
			SYNTAX	INTEGER
			MAX-ACCESS	read-only
			STATUS	current
			::= { hmWanMbusDC 38 }

hmWanMbusDCValue10		OBJECT-TYPE
			SYNTAX	INTEGER
			MAX-ACCESS	read-only
			STATUS	current
			::= { hmWanMbusDC 39 }

hmWanMbusDCVIF11		OBJECT-TYPE
			SYNTAX	INTEGER
			MAX-ACCESS	read-only
			STATUS	current
			::= { hmWanMbusDC 40 }

hmWanMbusDCValue11		OBJECT-TYPE
			SYNTAX	INTEGER
			MAX-ACCESS	read-only
			STATUS	current
			::= { hmWanMbusDC 41 }

hmWanMbusDCVIF12		OBJECT-TYPE
			SYNTAX	INTEGER
			MAX-ACCESS	read-only
			STATUS	current
			::= { hmWanMbusDC 42 }

hmWanMbusDCValue12		OBJECT-TYPE
			SYNTAX	INTEGER
			MAX-ACCESS	read-only
			STATUS	current
			::= { hmWanMbusDC 43 }

hmWanMbusDCVIF13		OBJECT-TYPE
			SYNTAX	INTEGER
			MAX-ACCESS	read-only
			STATUS	current
			::= { hmWanMbusDC 44 }

hmWanMbusDCValue13		OBJECT-TYPE
			SYNTAX	INTEGER
			MAX-ACCESS	read-only
			STATUS	current
			::= { hmWanMbusDC 45 }

hmWanMbusDCVIF14		OBJECT-TYPE
			SYNTAX	INTEGER
			MAX-ACCESS	read-only
			STATUS	current
			::= { hmWanMbusDC 46 }

hmWanMbusDCValue14		OBJECT-TYPE
			SYNTAX	INTEGER
			MAX-ACCESS	read-only
			STATUS	current
			::= { hmWanMbusDC 47 }

hmWanMbusDCVIF15		OBJECT-TYPE
			SYNTAX	INTEGER
			MAX-ACCESS	read-only
			STATUS	current
			::= { hmWanMbusDC 48 }

hmWanMbusDCValue15		OBJECT-TYPE
			SYNTAX	INTEGER
			MAX-ACCESS	read-only
			STATUS	current
			::= { hmWanMbusDC 49 }

hmWanMbusDCVIF16		OBJECT-TYPE
			SYNTAX	INTEGER
			MAX-ACCESS	read-only
			STATUS	current
			::= { hmWanMbusDC 50 }

hmWanMbusDCValue16		OBJECT-TYPE
			SYNTAX	INTEGER
			MAX-ACCESS	read-only
			STATUS	current
			::= { hmWanMbusDC 51 }

hmWanMbusDCVIF17		OBJECT-TYPE
			SYNTAX	INTEGER
			MAX-ACCESS	read-only
			STATUS	current
			::= { hmWanMbusDC 52 }

hmWanMbusDCValue17		OBJECT-TYPE
			SYNTAX	INTEGER
			MAX-ACCESS	read-only
			STATUS	current
			::= { hmWanMbusDC 53 }

hmWanMbusDCVIF18		OBJECT-TYPE
			SYNTAX	INTEGER
			MAX-ACCESS	read-only
			STATUS	current
			::= { hmWanMbusDC 54 }

hmWanMbusDCValue18		OBJECT-TYPE
			SYNTAX	INTEGER
			MAX-ACCESS	read-only
			STATUS	current
			::= { hmWanMbusDC 55 }

hmWanMbusDCVIF19		OBJECT-TYPE
			SYNTAX	INTEGER
			MAX-ACCESS	read-only
			STATUS	current
			::= { hmWanMbusDC 56 }

hmWanMbusDCValue19		OBJECT-TYPE
			SYNTAX	INTEGER
			MAX-ACCESS	read-only
			STATUS	current
			::= { hmWanMbusDC 57 }

hmWanMbusDCVIF1A		OBJECT-TYPE
			SYNTAX	INTEGER
			MAX-ACCESS	read-only
			STATUS	current
			::= { hmWanMbusDC 58 }

hmWanMbusDCValue1A		OBJECT-TYPE
			SYNTAX	INTEGER
			MAX-ACCESS	read-only
			STATUS	current
			::= { hmWanMbusDC 59 }

hmWanMbusDCVIF1B		OBJECT-TYPE
			SYNTAX	INTEGER
			MAX-ACCESS	read-only
			STATUS	current
			::= { hmWanMbusDC 60 }

hmWanMbusDCValue1B		OBJECT-TYPE
			SYNTAX	INTEGER
			MAX-ACCESS	read-only
			STATUS	current
			::= { hmWanMbusDC 61 }

hmWanMbusDCVIF1C		OBJECT-TYPE
			SYNTAX	INTEGER
			MAX-ACCESS	read-only
			STATUS	current
			::= { hmWanMbusDC 62 }

hmWanMbusDCValue1C		OBJECT-TYPE
			SYNTAX	INTEGER
			MAX-ACCESS	read-only
			STATUS	current
			::= { hmWanMbusDC 63 }

hmWanMbusDCVIF1D		OBJECT-TYPE
			SYNTAX	INTEGER
			MAX-ACCESS	read-only
			STATUS	current
			::= { hmWanMbusDC 64 }

hmWanMbusDCValue1D		OBJECT-TYPE
			SYNTAX	INTEGER
			MAX-ACCESS	read-only
			STATUS	current
			::= { hmWanMbusDC 65 }

hmWanMbusDCVIF1E		OBJECT-TYPE
			SYNTAX	INTEGER
			MAX-ACCESS	read-only
			STATUS	current
			::= { hmWanMbusDC 66 }

hmWanMbusDCValue1E		OBJECT-TYPE
			SYNTAX	INTEGER
			MAX-ACCESS	read-only
			STATUS	current
			::= { hmWanMbusDC 67 }

hmWanMbusDCVIF1F		OBJECT-TYPE
			SYNTAX	INTEGER
			MAX-ACCESS	read-only
			STATUS	current
			::= { hmWanMbusDC 68 }

hmWanMbusDCValue1F		OBJECT-TYPE
			SYNTAX	INTEGER
			MAX-ACCESS	read-only
			STATUS	current
			::= { hmWanMbusDC 69 }

hmWanMbusDCVIF20		OBJECT-TYPE
			SYNTAX	INTEGER
			MAX-ACCESS	read-only
			STATUS	current
			::= { hmWanMbusDC 70 }

hmWanMbusDCValue20		OBJECT-TYPE
			SYNTAX	INTEGER
			MAX-ACCESS	read-only
			STATUS	current
			::= { hmWanMbusDC 71 }

hmWanMbusDCVIF21		OBJECT-TYPE
			SYNTAX	INTEGER
			MAX-ACCESS	read-only
			STATUS	current
			::= { hmWanMbusDC 72 }

hmWanMbusDCValue21		OBJECT-TYPE
			SYNTAX	INTEGER
			MAX-ACCESS	read-only
			STATUS	current
			::= { hmWanMbusDC 73 }

hmWanMbusDCVIF22		OBJECT-TYPE
			SYNTAX	INTEGER
			MAX-ACCESS	read-only
			STATUS	current
			::= { hmWanMbusDC 74 }

hmWanMbusDCValue22		OBJECT-TYPE
			SYNTAX	INTEGER
			MAX-ACCESS	read-only
			STATUS	current
			::= { hmWanMbusDC 75 }

hmWanMbusDCVIF23		OBJECT-TYPE
			SYNTAX	INTEGER
			MAX-ACCESS	read-only
			STATUS	current
			::= { hmWanMbusDC 76 }

hmWanMbusDCValue23		OBJECT-TYPE
			SYNTAX	INTEGER
			MAX-ACCESS	read-only
			STATUS	current
			::= { hmWanMbusDC 77 }

hmWanMbusDCVIF24		OBJECT-TYPE
			SYNTAX	INTEGER
			MAX-ACCESS	read-only
			STATUS	current
			::= { hmWanMbusDC 78 }

hmWanMbusDCValue24		OBJECT-TYPE
			SYNTAX	INTEGER
			MAX-ACCESS	read-only
			STATUS	current
			::= { hmWanMbusDC 79 }

hmWanMbusDCVIF25		OBJECT-TYPE
			SYNTAX	INTEGER
			MAX-ACCESS	read-only
			STATUS	current
			::= { hmWanMbusDC 80 }

hmWanMbusDCValue25		OBJECT-TYPE
			SYNTAX	INTEGER
			MAX-ACCESS	read-only
			STATUS	current
			::= { hmWanMbusDC 81 }

hmWanMbusDCVIF26		OBJECT-TYPE
			SYNTAX	INTEGER
			MAX-ACCESS	read-only
			STATUS	current
			::= { hmWanMbusDC 82 }

hmWanMbusDCValue26		OBJECT-TYPE
			SYNTAX	INTEGER
			MAX-ACCESS	read-only
			STATUS	current
			::= { hmWanMbusDC 83 }

hmWanMbusDCVIF27		OBJECT-TYPE
			SYNTAX	INTEGER
			MAX-ACCESS	read-only
			STATUS	current
			::= { hmWanMbusDC 84 }

hmWanMbusDCValue27		OBJECT-TYPE
			SYNTAX	INTEGER
			MAX-ACCESS	read-only
			STATUS	current
			::= { hmWanMbusDC 85 }

hmWanMbusDCVIF28		OBJECT-TYPE
			SYNTAX	INTEGER
			MAX-ACCESS	read-only
			STATUS	current
			::= { hmWanMbusDC 86 }

hmWanMbusDCValue28		OBJECT-TYPE
			SYNTAX	INTEGER
			MAX-ACCESS	read-only
			STATUS	current
			::= { hmWanMbusDC 87 }

hmWanMbusDCVIF29		OBJECT-TYPE
			SYNTAX	INTEGER
			MAX-ACCESS	read-only
			STATUS	current
			::= { hmWanMbusDC 88 }

hmWanMbusDCValue29		OBJECT-TYPE
			SYNTAX	INTEGER
			MAX-ACCESS	read-only
			STATUS	current
			::= { hmWanMbusDC 89 }

hmWanMbusDCVIF2A		OBJECT-TYPE
			SYNTAX	INTEGER
			MAX-ACCESS	read-only
			STATUS	current
			::= { hmWanMbusDC 90 }

hmWanMbusDCValue2A		OBJECT-TYPE
			SYNTAX	INTEGER
			MAX-ACCESS	read-only
			STATUS	current
			::= { hmWanMbusDC 91 }

hmWanMbusDCVIF2B		OBJECT-TYPE
			SYNTAX	INTEGER
			MAX-ACCESS	read-only
			STATUS	current
			::= { hmWanMbusDC 92 }

hmWanMbusDCValue2B		OBJECT-TYPE
			SYNTAX	INTEGER
			MAX-ACCESS	read-only
			STATUS	current
			::= { hmWanMbusDC 93 }

hmWanMbusDCVIF2C		OBJECT-TYPE
			SYNTAX	INTEGER
			MAX-ACCESS	read-only
			STATUS	current
			::= { hmWanMbusDC 94 }

hmWanMbusDCValue2C		OBJECT-TYPE
			SYNTAX	INTEGER
			MAX-ACCESS	read-only
			STATUS	current
			::= { hmWanMbusDC 95 }

hmWanMbusDCVIF2D		OBJECT-TYPE
			SYNTAX	INTEGER
			MAX-ACCESS	read-only
			STATUS	current
			::= { hmWanMbusDC 96 }

hmWanMbusDCValue2D		OBJECT-TYPE
			SYNTAX	INTEGER
			MAX-ACCESS	read-only
			STATUS	current
			::= { hmWanMbusDC 97 }

hmWanMbusDCVIF2E		OBJECT-TYPE
			SYNTAX	INTEGER
			MAX-ACCESS	read-only
			STATUS	current
			::= { hmWanMbusDC 98 }

hmWanMbusDCValue2E		OBJECT-TYPE
			SYNTAX	INTEGER
			MAX-ACCESS	read-only
			STATUS	current
			::= { hmWanMbusDC 99 }

hmWanMbusDCVIF2F		OBJECT-TYPE
			SYNTAX	INTEGER
			MAX-ACCESS	read-only
			STATUS	current
			::= { hmWanMbusDC 100 }

hmWanMbusDCValue2F		OBJECT-TYPE
			SYNTAX	INTEGER
			MAX-ACCESS	read-only
			STATUS	current
			::= { hmWanMbusDC 101 }

hmWanMbusDD			OBJECT IDENTIFIER ::= { hmWanMbus 221 }

hmWanMbusDDIdNumber		OBJECT-TYPE
			SYNTAX	Gauge32
			MAX-ACCESS	read-only
			STATUS	current
			::= { hmWanMbusDD 1 }

hmWanMbusDDManufacturer	OBJECT-TYPE
			SYNTAX	Gauge32
			MAX-ACCESS	read-only
			STATUS	current
			::= { hmWanMbusDD 2 }

hmWanMbusDDVersion		OBJECT-TYPE
			SYNTAX	Gauge32
			MAX-ACCESS	read-only
			STATUS	current
			::= { hmWanMbusDD 3 }

hmWanMbusDDMedium		OBJECT-TYPE
			SYNTAX	Gauge32
			MAX-ACCESS	read-only
			STATUS	current
			::= { hmWanMbusDD 4 }

hmWanMbusDDStatus		OBJECT-TYPE
			SYNTAX	Gauge32
			MAX-ACCESS	read-only
			STATUS	current
			::= { hmWanMbusDD 5 }

hmWanMbusDDVIF00		OBJECT-TYPE
			SYNTAX	INTEGER
			MAX-ACCESS	read-only
			STATUS	current
			::= { hmWanMbusDD 6 }

hmWanMbusDDValue00		OBJECT-TYPE
			SYNTAX	INTEGER
			MAX-ACCESS	read-only
			STATUS	current
			::= { hmWanMbusDD 7 }

hmWanMbusDDVIF01		OBJECT-TYPE
			SYNTAX	INTEGER
			MAX-ACCESS	read-only
			STATUS	current
			::= { hmWanMbusDD 8 }

hmWanMbusDDValue01		OBJECT-TYPE
			SYNTAX	INTEGER
			MAX-ACCESS	read-only
			STATUS	current
			::= { hmWanMbusDD 9 }

hmWanMbusDDVIF02		OBJECT-TYPE
			SYNTAX	INTEGER
			MAX-ACCESS	read-only
			STATUS	current
			::= { hmWanMbusDD 10 }

hmWanMbusDDValue02		OBJECT-TYPE
			SYNTAX	INTEGER
			MAX-ACCESS	read-only
			STATUS	current
			::= { hmWanMbusDD 11 }

hmWanMbusDDVIF03		OBJECT-TYPE
			SYNTAX	INTEGER
			MAX-ACCESS	read-only
			STATUS	current
			::= { hmWanMbusDD 12 }

hmWanMbusDDValue03		OBJECT-TYPE
			SYNTAX	INTEGER
			MAX-ACCESS	read-only
			STATUS	current
			::= { hmWanMbusDD 13 }

hmWanMbusDDVIF04		OBJECT-TYPE
			SYNTAX	INTEGER
			MAX-ACCESS	read-only
			STATUS	current
			::= { hmWanMbusDD 14 }

hmWanMbusDDValue04		OBJECT-TYPE
			SYNTAX	INTEGER
			MAX-ACCESS	read-only
			STATUS	current
			::= { hmWanMbusDD 15 }

hmWanMbusDDVIF05		OBJECT-TYPE
			SYNTAX	INTEGER
			MAX-ACCESS	read-only
			STATUS	current
			::= { hmWanMbusDD 16 }

hmWanMbusDDValue05		OBJECT-TYPE
			SYNTAX	INTEGER
			MAX-ACCESS	read-only
			STATUS	current
			::= { hmWanMbusDD 17 }

hmWanMbusDDVIF06		OBJECT-TYPE
			SYNTAX	INTEGER
			MAX-ACCESS	read-only
			STATUS	current
			::= { hmWanMbusDD 18 }

hmWanMbusDDValue06		OBJECT-TYPE
			SYNTAX	INTEGER
			MAX-ACCESS	read-only
			STATUS	current
			::= { hmWanMbusDD 19 }

hmWanMbusDDVIF07		OBJECT-TYPE
			SYNTAX	INTEGER
			MAX-ACCESS	read-only
			STATUS	current
			::= { hmWanMbusDD 20 }

hmWanMbusDDValue07		OBJECT-TYPE
			SYNTAX	INTEGER
			MAX-ACCESS	read-only
			STATUS	current
			::= { hmWanMbusDD 21 }

hmWanMbusDDVIF08		OBJECT-TYPE
			SYNTAX	INTEGER
			MAX-ACCESS	read-only
			STATUS	current
			::= { hmWanMbusDD 22 }

hmWanMbusDDValue08		OBJECT-TYPE
			SYNTAX	INTEGER
			MAX-ACCESS	read-only
			STATUS	current
			::= { hmWanMbusDD 23 }

hmWanMbusDDVIF09		OBJECT-TYPE
			SYNTAX	INTEGER
			MAX-ACCESS	read-only
			STATUS	current
			::= { hmWanMbusDD 24 }

hmWanMbusDDValue09		OBJECT-TYPE
			SYNTAX	INTEGER
			MAX-ACCESS	read-only
			STATUS	current
			::= { hmWanMbusDD 25 }

hmWanMbusDDVIF0A		OBJECT-TYPE
			SYNTAX	INTEGER
			MAX-ACCESS	read-only
			STATUS	current
			::= { hmWanMbusDD 26 }

hmWanMbusDDValue0A		OBJECT-TYPE
			SYNTAX	INTEGER
			MAX-ACCESS	read-only
			STATUS	current
			::= { hmWanMbusDD 27 }

hmWanMbusDDVIF0B		OBJECT-TYPE
			SYNTAX	INTEGER
			MAX-ACCESS	read-only
			STATUS	current
			::= { hmWanMbusDD 28 }

hmWanMbusDDValue0B		OBJECT-TYPE
			SYNTAX	INTEGER
			MAX-ACCESS	read-only
			STATUS	current
			::= { hmWanMbusDD 29 }

hmWanMbusDDVIF0C		OBJECT-TYPE
			SYNTAX	INTEGER
			MAX-ACCESS	read-only
			STATUS	current
			::= { hmWanMbusDD 30 }

hmWanMbusDDValue0C		OBJECT-TYPE
			SYNTAX	INTEGER
			MAX-ACCESS	read-only
			STATUS	current
			::= { hmWanMbusDD 31 }

hmWanMbusDDVIF0D		OBJECT-TYPE
			SYNTAX	INTEGER
			MAX-ACCESS	read-only
			STATUS	current
			::= { hmWanMbusDD 32 }

hmWanMbusDDValue0D		OBJECT-TYPE
			SYNTAX	INTEGER
			MAX-ACCESS	read-only
			STATUS	current
			::= { hmWanMbusDD 33 }

hmWanMbusDDVIF0E		OBJECT-TYPE
			SYNTAX	INTEGER
			MAX-ACCESS	read-only
			STATUS	current
			::= { hmWanMbusDD 34 }

hmWanMbusDDValue0E		OBJECT-TYPE
			SYNTAX	INTEGER
			MAX-ACCESS	read-only
			STATUS	current
			::= { hmWanMbusDD 35 }

hmWanMbusDDVIF0F		OBJECT-TYPE
			SYNTAX	INTEGER
			MAX-ACCESS	read-only
			STATUS	current
			::= { hmWanMbusDD 36 }

hmWanMbusDDValue0F		OBJECT-TYPE
			SYNTAX	INTEGER
			MAX-ACCESS	read-only
			STATUS	current
			::= { hmWanMbusDD 37 }

hmWanMbusDDVIF10		OBJECT-TYPE
			SYNTAX	INTEGER
			MAX-ACCESS	read-only
			STATUS	current
			::= { hmWanMbusDD 38 }

hmWanMbusDDValue10		OBJECT-TYPE
			SYNTAX	INTEGER
			MAX-ACCESS	read-only
			STATUS	current
			::= { hmWanMbusDD 39 }

hmWanMbusDDVIF11		OBJECT-TYPE
			SYNTAX	INTEGER
			MAX-ACCESS	read-only
			STATUS	current
			::= { hmWanMbusDD 40 }

hmWanMbusDDValue11		OBJECT-TYPE
			SYNTAX	INTEGER
			MAX-ACCESS	read-only
			STATUS	current
			::= { hmWanMbusDD 41 }

hmWanMbusDDVIF12		OBJECT-TYPE
			SYNTAX	INTEGER
			MAX-ACCESS	read-only
			STATUS	current
			::= { hmWanMbusDD 42 }

hmWanMbusDDValue12		OBJECT-TYPE
			SYNTAX	INTEGER
			MAX-ACCESS	read-only
			STATUS	current
			::= { hmWanMbusDD 43 }

hmWanMbusDDVIF13		OBJECT-TYPE
			SYNTAX	INTEGER
			MAX-ACCESS	read-only
			STATUS	current
			::= { hmWanMbusDD 44 }

hmWanMbusDDValue13		OBJECT-TYPE
			SYNTAX	INTEGER
			MAX-ACCESS	read-only
			STATUS	current
			::= { hmWanMbusDD 45 }

hmWanMbusDDVIF14		OBJECT-TYPE
			SYNTAX	INTEGER
			MAX-ACCESS	read-only
			STATUS	current
			::= { hmWanMbusDD 46 }

hmWanMbusDDValue14		OBJECT-TYPE
			SYNTAX	INTEGER
			MAX-ACCESS	read-only
			STATUS	current
			::= { hmWanMbusDD 47 }

hmWanMbusDDVIF15		OBJECT-TYPE
			SYNTAX	INTEGER
			MAX-ACCESS	read-only
			STATUS	current
			::= { hmWanMbusDD 48 }

hmWanMbusDDValue15		OBJECT-TYPE
			SYNTAX	INTEGER
			MAX-ACCESS	read-only
			STATUS	current
			::= { hmWanMbusDD 49 }

hmWanMbusDDVIF16		OBJECT-TYPE
			SYNTAX	INTEGER
			MAX-ACCESS	read-only
			STATUS	current
			::= { hmWanMbusDD 50 }

hmWanMbusDDValue16		OBJECT-TYPE
			SYNTAX	INTEGER
			MAX-ACCESS	read-only
			STATUS	current
			::= { hmWanMbusDD 51 }

hmWanMbusDDVIF17		OBJECT-TYPE
			SYNTAX	INTEGER
			MAX-ACCESS	read-only
			STATUS	current
			::= { hmWanMbusDD 52 }

hmWanMbusDDValue17		OBJECT-TYPE
			SYNTAX	INTEGER
			MAX-ACCESS	read-only
			STATUS	current
			::= { hmWanMbusDD 53 }

hmWanMbusDDVIF18		OBJECT-TYPE
			SYNTAX	INTEGER
			MAX-ACCESS	read-only
			STATUS	current
			::= { hmWanMbusDD 54 }

hmWanMbusDDValue18		OBJECT-TYPE
			SYNTAX	INTEGER
			MAX-ACCESS	read-only
			STATUS	current
			::= { hmWanMbusDD 55 }

hmWanMbusDDVIF19		OBJECT-TYPE
			SYNTAX	INTEGER
			MAX-ACCESS	read-only
			STATUS	current
			::= { hmWanMbusDD 56 }

hmWanMbusDDValue19		OBJECT-TYPE
			SYNTAX	INTEGER
			MAX-ACCESS	read-only
			STATUS	current
			::= { hmWanMbusDD 57 }

hmWanMbusDDVIF1A		OBJECT-TYPE
			SYNTAX	INTEGER
			MAX-ACCESS	read-only
			STATUS	current
			::= { hmWanMbusDD 58 }

hmWanMbusDDValue1A		OBJECT-TYPE
			SYNTAX	INTEGER
			MAX-ACCESS	read-only
			STATUS	current
			::= { hmWanMbusDD 59 }

hmWanMbusDDVIF1B		OBJECT-TYPE
			SYNTAX	INTEGER
			MAX-ACCESS	read-only
			STATUS	current
			::= { hmWanMbusDD 60 }

hmWanMbusDDValue1B		OBJECT-TYPE
			SYNTAX	INTEGER
			MAX-ACCESS	read-only
			STATUS	current
			::= { hmWanMbusDD 61 }

hmWanMbusDDVIF1C		OBJECT-TYPE
			SYNTAX	INTEGER
			MAX-ACCESS	read-only
			STATUS	current
			::= { hmWanMbusDD 62 }

hmWanMbusDDValue1C		OBJECT-TYPE
			SYNTAX	INTEGER
			MAX-ACCESS	read-only
			STATUS	current
			::= { hmWanMbusDD 63 }

hmWanMbusDDVIF1D		OBJECT-TYPE
			SYNTAX	INTEGER
			MAX-ACCESS	read-only
			STATUS	current
			::= { hmWanMbusDD 64 }

hmWanMbusDDValue1D		OBJECT-TYPE
			SYNTAX	INTEGER
			MAX-ACCESS	read-only
			STATUS	current
			::= { hmWanMbusDD 65 }

hmWanMbusDDVIF1E		OBJECT-TYPE
			SYNTAX	INTEGER
			MAX-ACCESS	read-only
			STATUS	current
			::= { hmWanMbusDD 66 }

hmWanMbusDDValue1E		OBJECT-TYPE
			SYNTAX	INTEGER
			MAX-ACCESS	read-only
			STATUS	current
			::= { hmWanMbusDD 67 }

hmWanMbusDDVIF1F		OBJECT-TYPE
			SYNTAX	INTEGER
			MAX-ACCESS	read-only
			STATUS	current
			::= { hmWanMbusDD 68 }

hmWanMbusDDValue1F		OBJECT-TYPE
			SYNTAX	INTEGER
			MAX-ACCESS	read-only
			STATUS	current
			::= { hmWanMbusDD 69 }

hmWanMbusDDVIF20		OBJECT-TYPE
			SYNTAX	INTEGER
			MAX-ACCESS	read-only
			STATUS	current
			::= { hmWanMbusDD 70 }

hmWanMbusDDValue20		OBJECT-TYPE
			SYNTAX	INTEGER
			MAX-ACCESS	read-only
			STATUS	current
			::= { hmWanMbusDD 71 }

hmWanMbusDDVIF21		OBJECT-TYPE
			SYNTAX	INTEGER
			MAX-ACCESS	read-only
			STATUS	current
			::= { hmWanMbusDD 72 }

hmWanMbusDDValue21		OBJECT-TYPE
			SYNTAX	INTEGER
			MAX-ACCESS	read-only
			STATUS	current
			::= { hmWanMbusDD 73 }

hmWanMbusDDVIF22		OBJECT-TYPE
			SYNTAX	INTEGER
			MAX-ACCESS	read-only
			STATUS	current
			::= { hmWanMbusDD 74 }

hmWanMbusDDValue22		OBJECT-TYPE
			SYNTAX	INTEGER
			MAX-ACCESS	read-only
			STATUS	current
			::= { hmWanMbusDD 75 }

hmWanMbusDDVIF23		OBJECT-TYPE
			SYNTAX	INTEGER
			MAX-ACCESS	read-only
			STATUS	current
			::= { hmWanMbusDD 76 }

hmWanMbusDDValue23		OBJECT-TYPE
			SYNTAX	INTEGER
			MAX-ACCESS	read-only
			STATUS	current
			::= { hmWanMbusDD 77 }

hmWanMbusDDVIF24		OBJECT-TYPE
			SYNTAX	INTEGER
			MAX-ACCESS	read-only
			STATUS	current
			::= { hmWanMbusDD 78 }

hmWanMbusDDValue24		OBJECT-TYPE
			SYNTAX	INTEGER
			MAX-ACCESS	read-only
			STATUS	current
			::= { hmWanMbusDD 79 }

hmWanMbusDDVIF25		OBJECT-TYPE
			SYNTAX	INTEGER
			MAX-ACCESS	read-only
			STATUS	current
			::= { hmWanMbusDD 80 }

hmWanMbusDDValue25		OBJECT-TYPE
			SYNTAX	INTEGER
			MAX-ACCESS	read-only
			STATUS	current
			::= { hmWanMbusDD 81 }

hmWanMbusDDVIF26		OBJECT-TYPE
			SYNTAX	INTEGER
			MAX-ACCESS	read-only
			STATUS	current
			::= { hmWanMbusDD 82 }

hmWanMbusDDValue26		OBJECT-TYPE
			SYNTAX	INTEGER
			MAX-ACCESS	read-only
			STATUS	current
			::= { hmWanMbusDD 83 }

hmWanMbusDDVIF27		OBJECT-TYPE
			SYNTAX	INTEGER
			MAX-ACCESS	read-only
			STATUS	current
			::= { hmWanMbusDD 84 }

hmWanMbusDDValue27		OBJECT-TYPE
			SYNTAX	INTEGER
			MAX-ACCESS	read-only
			STATUS	current
			::= { hmWanMbusDD 85 }

hmWanMbusDDVIF28		OBJECT-TYPE
			SYNTAX	INTEGER
			MAX-ACCESS	read-only
			STATUS	current
			::= { hmWanMbusDD 86 }

hmWanMbusDDValue28		OBJECT-TYPE
			SYNTAX	INTEGER
			MAX-ACCESS	read-only
			STATUS	current
			::= { hmWanMbusDD 87 }

hmWanMbusDDVIF29		OBJECT-TYPE
			SYNTAX	INTEGER
			MAX-ACCESS	read-only
			STATUS	current
			::= { hmWanMbusDD 88 }

hmWanMbusDDValue29		OBJECT-TYPE
			SYNTAX	INTEGER
			MAX-ACCESS	read-only
			STATUS	current
			::= { hmWanMbusDD 89 }

hmWanMbusDDVIF2A		OBJECT-TYPE
			SYNTAX	INTEGER
			MAX-ACCESS	read-only
			STATUS	current
			::= { hmWanMbusDD 90 }

hmWanMbusDDValue2A		OBJECT-TYPE
			SYNTAX	INTEGER
			MAX-ACCESS	read-only
			STATUS	current
			::= { hmWanMbusDD 91 }

hmWanMbusDDVIF2B		OBJECT-TYPE
			SYNTAX	INTEGER
			MAX-ACCESS	read-only
			STATUS	current
			::= { hmWanMbusDD 92 }

hmWanMbusDDValue2B		OBJECT-TYPE
			SYNTAX	INTEGER
			MAX-ACCESS	read-only
			STATUS	current
			::= { hmWanMbusDD 93 }

hmWanMbusDDVIF2C		OBJECT-TYPE
			SYNTAX	INTEGER
			MAX-ACCESS	read-only
			STATUS	current
			::= { hmWanMbusDD 94 }

hmWanMbusDDValue2C		OBJECT-TYPE
			SYNTAX	INTEGER
			MAX-ACCESS	read-only
			STATUS	current
			::= { hmWanMbusDD 95 }

hmWanMbusDDVIF2D		OBJECT-TYPE
			SYNTAX	INTEGER
			MAX-ACCESS	read-only
			STATUS	current
			::= { hmWanMbusDD 96 }

hmWanMbusDDValue2D		OBJECT-TYPE
			SYNTAX	INTEGER
			MAX-ACCESS	read-only
			STATUS	current
			::= { hmWanMbusDD 97 }

hmWanMbusDDVIF2E		OBJECT-TYPE
			SYNTAX	INTEGER
			MAX-ACCESS	read-only
			STATUS	current
			::= { hmWanMbusDD 98 }

hmWanMbusDDValue2E		OBJECT-TYPE
			SYNTAX	INTEGER
			MAX-ACCESS	read-only
			STATUS	current
			::= { hmWanMbusDD 99 }

hmWanMbusDDVIF2F		OBJECT-TYPE
			SYNTAX	INTEGER
			MAX-ACCESS	read-only
			STATUS	current
			::= { hmWanMbusDD 100 }

hmWanMbusDDValue2F		OBJECT-TYPE
			SYNTAX	INTEGER
			MAX-ACCESS	read-only
			STATUS	current
			::= { hmWanMbusDD 101 }

hmWanMbusDE			OBJECT IDENTIFIER ::= { hmWanMbus 222 }

hmWanMbusDEIdNumber		OBJECT-TYPE
			SYNTAX	Gauge32
			MAX-ACCESS	read-only
			STATUS	current
			::= { hmWanMbusDE 1 }

hmWanMbusDEManufacturer	OBJECT-TYPE
			SYNTAX	Gauge32
			MAX-ACCESS	read-only
			STATUS	current
			::= { hmWanMbusDE 2 }

hmWanMbusDEVersion		OBJECT-TYPE
			SYNTAX	Gauge32
			MAX-ACCESS	read-only
			STATUS	current
			::= { hmWanMbusDE 3 }

hmWanMbusDEMedium		OBJECT-TYPE
			SYNTAX	Gauge32
			MAX-ACCESS	read-only
			STATUS	current
			::= { hmWanMbusDE 4 }

hmWanMbusDEStatus		OBJECT-TYPE
			SYNTAX	Gauge32
			MAX-ACCESS	read-only
			STATUS	current
			::= { hmWanMbusDE 5 }

hmWanMbusDEVIF00		OBJECT-TYPE
			SYNTAX	INTEGER
			MAX-ACCESS	read-only
			STATUS	current
			::= { hmWanMbusDE 6 }

hmWanMbusDEValue00		OBJECT-TYPE
			SYNTAX	INTEGER
			MAX-ACCESS	read-only
			STATUS	current
			::= { hmWanMbusDE 7 }

hmWanMbusDEVIF01		OBJECT-TYPE
			SYNTAX	INTEGER
			MAX-ACCESS	read-only
			STATUS	current
			::= { hmWanMbusDE 8 }

hmWanMbusDEValue01		OBJECT-TYPE
			SYNTAX	INTEGER
			MAX-ACCESS	read-only
			STATUS	current
			::= { hmWanMbusDE 9 }

hmWanMbusDEVIF02		OBJECT-TYPE
			SYNTAX	INTEGER
			MAX-ACCESS	read-only
			STATUS	current
			::= { hmWanMbusDE 10 }

hmWanMbusDEValue02		OBJECT-TYPE
			SYNTAX	INTEGER
			MAX-ACCESS	read-only
			STATUS	current
			::= { hmWanMbusDE 11 }

hmWanMbusDEVIF03		OBJECT-TYPE
			SYNTAX	INTEGER
			MAX-ACCESS	read-only
			STATUS	current
			::= { hmWanMbusDE 12 }

hmWanMbusDEValue03		OBJECT-TYPE
			SYNTAX	INTEGER
			MAX-ACCESS	read-only
			STATUS	current
			::= { hmWanMbusDE 13 }

hmWanMbusDEVIF04		OBJECT-TYPE
			SYNTAX	INTEGER
			MAX-ACCESS	read-only
			STATUS	current
			::= { hmWanMbusDE 14 }

hmWanMbusDEValue04		OBJECT-TYPE
			SYNTAX	INTEGER
			MAX-ACCESS	read-only
			STATUS	current
			::= { hmWanMbusDE 15 }

hmWanMbusDEVIF05		OBJECT-TYPE
			SYNTAX	INTEGER
			MAX-ACCESS	read-only
			STATUS	current
			::= { hmWanMbusDE 16 }

hmWanMbusDEValue05		OBJECT-TYPE
			SYNTAX	INTEGER
			MAX-ACCESS	read-only
			STATUS	current
			::= { hmWanMbusDE 17 }

hmWanMbusDEVIF06		OBJECT-TYPE
			SYNTAX	INTEGER
			MAX-ACCESS	read-only
			STATUS	current
			::= { hmWanMbusDE 18 }

hmWanMbusDEValue06		OBJECT-TYPE
			SYNTAX	INTEGER
			MAX-ACCESS	read-only
			STATUS	current
			::= { hmWanMbusDE 19 }

hmWanMbusDEVIF07		OBJECT-TYPE
			SYNTAX	INTEGER
			MAX-ACCESS	read-only
			STATUS	current
			::= { hmWanMbusDE 20 }

hmWanMbusDEValue07		OBJECT-TYPE
			SYNTAX	INTEGER
			MAX-ACCESS	read-only
			STATUS	current
			::= { hmWanMbusDE 21 }

hmWanMbusDEVIF08		OBJECT-TYPE
			SYNTAX	INTEGER
			MAX-ACCESS	read-only
			STATUS	current
			::= { hmWanMbusDE 22 }

hmWanMbusDEValue08		OBJECT-TYPE
			SYNTAX	INTEGER
			MAX-ACCESS	read-only
			STATUS	current
			::= { hmWanMbusDE 23 }

hmWanMbusDEVIF09		OBJECT-TYPE
			SYNTAX	INTEGER
			MAX-ACCESS	read-only
			STATUS	current
			::= { hmWanMbusDE 24 }

hmWanMbusDEValue09		OBJECT-TYPE
			SYNTAX	INTEGER
			MAX-ACCESS	read-only
			STATUS	current
			::= { hmWanMbusDE 25 }

hmWanMbusDEVIF0A		OBJECT-TYPE
			SYNTAX	INTEGER
			MAX-ACCESS	read-only
			STATUS	current
			::= { hmWanMbusDE 26 }

hmWanMbusDEValue0A		OBJECT-TYPE
			SYNTAX	INTEGER
			MAX-ACCESS	read-only
			STATUS	current
			::= { hmWanMbusDE 27 }

hmWanMbusDEVIF0B		OBJECT-TYPE
			SYNTAX	INTEGER
			MAX-ACCESS	read-only
			STATUS	current
			::= { hmWanMbusDE 28 }

hmWanMbusDEValue0B		OBJECT-TYPE
			SYNTAX	INTEGER
			MAX-ACCESS	read-only
			STATUS	current
			::= { hmWanMbusDE 29 }

hmWanMbusDEVIF0C		OBJECT-TYPE
			SYNTAX	INTEGER
			MAX-ACCESS	read-only
			STATUS	current
			::= { hmWanMbusDE 30 }

hmWanMbusDEValue0C		OBJECT-TYPE
			SYNTAX	INTEGER
			MAX-ACCESS	read-only
			STATUS	current
			::= { hmWanMbusDE 31 }

hmWanMbusDEVIF0D		OBJECT-TYPE
			SYNTAX	INTEGER
			MAX-ACCESS	read-only
			STATUS	current
			::= { hmWanMbusDE 32 }

hmWanMbusDEValue0D		OBJECT-TYPE
			SYNTAX	INTEGER
			MAX-ACCESS	read-only
			STATUS	current
			::= { hmWanMbusDE 33 }

hmWanMbusDEVIF0E		OBJECT-TYPE
			SYNTAX	INTEGER
			MAX-ACCESS	read-only
			STATUS	current
			::= { hmWanMbusDE 34 }

hmWanMbusDEValue0E		OBJECT-TYPE
			SYNTAX	INTEGER
			MAX-ACCESS	read-only
			STATUS	current
			::= { hmWanMbusDE 35 }

hmWanMbusDEVIF0F		OBJECT-TYPE
			SYNTAX	INTEGER
			MAX-ACCESS	read-only
			STATUS	current
			::= { hmWanMbusDE 36 }

hmWanMbusDEValue0F		OBJECT-TYPE
			SYNTAX	INTEGER
			MAX-ACCESS	read-only
			STATUS	current
			::= { hmWanMbusDE 37 }

hmWanMbusDEVIF10		OBJECT-TYPE
			SYNTAX	INTEGER
			MAX-ACCESS	read-only
			STATUS	current
			::= { hmWanMbusDE 38 }

hmWanMbusDEValue10		OBJECT-TYPE
			SYNTAX	INTEGER
			MAX-ACCESS	read-only
			STATUS	current
			::= { hmWanMbusDE 39 }

hmWanMbusDEVIF11		OBJECT-TYPE
			SYNTAX	INTEGER
			MAX-ACCESS	read-only
			STATUS	current
			::= { hmWanMbusDE 40 }

hmWanMbusDEValue11		OBJECT-TYPE
			SYNTAX	INTEGER
			MAX-ACCESS	read-only
			STATUS	current
			::= { hmWanMbusDE 41 }

hmWanMbusDEVIF12		OBJECT-TYPE
			SYNTAX	INTEGER
			MAX-ACCESS	read-only
			STATUS	current
			::= { hmWanMbusDE 42 }

hmWanMbusDEValue12		OBJECT-TYPE
			SYNTAX	INTEGER
			MAX-ACCESS	read-only
			STATUS	current
			::= { hmWanMbusDE 43 }

hmWanMbusDEVIF13		OBJECT-TYPE
			SYNTAX	INTEGER
			MAX-ACCESS	read-only
			STATUS	current
			::= { hmWanMbusDE 44 }

hmWanMbusDEValue13		OBJECT-TYPE
			SYNTAX	INTEGER
			MAX-ACCESS	read-only
			STATUS	current
			::= { hmWanMbusDE 45 }

hmWanMbusDEVIF14		OBJECT-TYPE
			SYNTAX	INTEGER
			MAX-ACCESS	read-only
			STATUS	current
			::= { hmWanMbusDE 46 }

hmWanMbusDEValue14		OBJECT-TYPE
			SYNTAX	INTEGER
			MAX-ACCESS	read-only
			STATUS	current
			::= { hmWanMbusDE 47 }

hmWanMbusDEVIF15		OBJECT-TYPE
			SYNTAX	INTEGER
			MAX-ACCESS	read-only
			STATUS	current
			::= { hmWanMbusDE 48 }

hmWanMbusDEValue15		OBJECT-TYPE
			SYNTAX	INTEGER
			MAX-ACCESS	read-only
			STATUS	current
			::= { hmWanMbusDE 49 }

hmWanMbusDEVIF16		OBJECT-TYPE
			SYNTAX	INTEGER
			MAX-ACCESS	read-only
			STATUS	current
			::= { hmWanMbusDE 50 }

hmWanMbusDEValue16		OBJECT-TYPE
			SYNTAX	INTEGER
			MAX-ACCESS	read-only
			STATUS	current
			::= { hmWanMbusDE 51 }

hmWanMbusDEVIF17		OBJECT-TYPE
			SYNTAX	INTEGER
			MAX-ACCESS	read-only
			STATUS	current
			::= { hmWanMbusDE 52 }

hmWanMbusDEValue17		OBJECT-TYPE
			SYNTAX	INTEGER
			MAX-ACCESS	read-only
			STATUS	current
			::= { hmWanMbusDE 53 }

hmWanMbusDEVIF18		OBJECT-TYPE
			SYNTAX	INTEGER
			MAX-ACCESS	read-only
			STATUS	current
			::= { hmWanMbusDE 54 }

hmWanMbusDEValue18		OBJECT-TYPE
			SYNTAX	INTEGER
			MAX-ACCESS	read-only
			STATUS	current
			::= { hmWanMbusDE 55 }

hmWanMbusDEVIF19		OBJECT-TYPE
			SYNTAX	INTEGER
			MAX-ACCESS	read-only
			STATUS	current
			::= { hmWanMbusDE 56 }

hmWanMbusDEValue19		OBJECT-TYPE
			SYNTAX	INTEGER
			MAX-ACCESS	read-only
			STATUS	current
			::= { hmWanMbusDE 57 }

hmWanMbusDEVIF1A		OBJECT-TYPE
			SYNTAX	INTEGER
			MAX-ACCESS	read-only
			STATUS	current
			::= { hmWanMbusDE 58 }

hmWanMbusDEValue1A		OBJECT-TYPE
			SYNTAX	INTEGER
			MAX-ACCESS	read-only
			STATUS	current
			::= { hmWanMbusDE 59 }

hmWanMbusDEVIF1B		OBJECT-TYPE
			SYNTAX	INTEGER
			MAX-ACCESS	read-only
			STATUS	current
			::= { hmWanMbusDE 60 }

hmWanMbusDEValue1B		OBJECT-TYPE
			SYNTAX	INTEGER
			MAX-ACCESS	read-only
			STATUS	current
			::= { hmWanMbusDE 61 }

hmWanMbusDEVIF1C		OBJECT-TYPE
			SYNTAX	INTEGER
			MAX-ACCESS	read-only
			STATUS	current
			::= { hmWanMbusDE 62 }

hmWanMbusDEValue1C		OBJECT-TYPE
			SYNTAX	INTEGER
			MAX-ACCESS	read-only
			STATUS	current
			::= { hmWanMbusDE 63 }

hmWanMbusDEVIF1D		OBJECT-TYPE
			SYNTAX	INTEGER
			MAX-ACCESS	read-only
			STATUS	current
			::= { hmWanMbusDE 64 }

hmWanMbusDEValue1D		OBJECT-TYPE
			SYNTAX	INTEGER
			MAX-ACCESS	read-only
			STATUS	current
			::= { hmWanMbusDE 65 }

hmWanMbusDEVIF1E		OBJECT-TYPE
			SYNTAX	INTEGER
			MAX-ACCESS	read-only
			STATUS	current
			::= { hmWanMbusDE 66 }

hmWanMbusDEValue1E		OBJECT-TYPE
			SYNTAX	INTEGER
			MAX-ACCESS	read-only
			STATUS	current
			::= { hmWanMbusDE 67 }

hmWanMbusDEVIF1F		OBJECT-TYPE
			SYNTAX	INTEGER
			MAX-ACCESS	read-only
			STATUS	current
			::= { hmWanMbusDE 68 }

hmWanMbusDEValue1F		OBJECT-TYPE
			SYNTAX	INTEGER
			MAX-ACCESS	read-only
			STATUS	current
			::= { hmWanMbusDE 69 }

hmWanMbusDEVIF20		OBJECT-TYPE
			SYNTAX	INTEGER
			MAX-ACCESS	read-only
			STATUS	current
			::= { hmWanMbusDE 70 }

hmWanMbusDEValue20		OBJECT-TYPE
			SYNTAX	INTEGER
			MAX-ACCESS	read-only
			STATUS	current
			::= { hmWanMbusDE 71 }

hmWanMbusDEVIF21		OBJECT-TYPE
			SYNTAX	INTEGER
			MAX-ACCESS	read-only
			STATUS	current
			::= { hmWanMbusDE 72 }

hmWanMbusDEValue21		OBJECT-TYPE
			SYNTAX	INTEGER
			MAX-ACCESS	read-only
			STATUS	current
			::= { hmWanMbusDE 73 }

hmWanMbusDEVIF22		OBJECT-TYPE
			SYNTAX	INTEGER
			MAX-ACCESS	read-only
			STATUS	current
			::= { hmWanMbusDE 74 }

hmWanMbusDEValue22		OBJECT-TYPE
			SYNTAX	INTEGER
			MAX-ACCESS	read-only
			STATUS	current
			::= { hmWanMbusDE 75 }

hmWanMbusDEVIF23		OBJECT-TYPE
			SYNTAX	INTEGER
			MAX-ACCESS	read-only
			STATUS	current
			::= { hmWanMbusDE 76 }

hmWanMbusDEValue23		OBJECT-TYPE
			SYNTAX	INTEGER
			MAX-ACCESS	read-only
			STATUS	current
			::= { hmWanMbusDE 77 }

hmWanMbusDEVIF24		OBJECT-TYPE
			SYNTAX	INTEGER
			MAX-ACCESS	read-only
			STATUS	current
			::= { hmWanMbusDE 78 }

hmWanMbusDEValue24		OBJECT-TYPE
			SYNTAX	INTEGER
			MAX-ACCESS	read-only
			STATUS	current
			::= { hmWanMbusDE 79 }

hmWanMbusDEVIF25		OBJECT-TYPE
			SYNTAX	INTEGER
			MAX-ACCESS	read-only
			STATUS	current
			::= { hmWanMbusDE 80 }

hmWanMbusDEValue25		OBJECT-TYPE
			SYNTAX	INTEGER
			MAX-ACCESS	read-only
			STATUS	current
			::= { hmWanMbusDE 81 }

hmWanMbusDEVIF26		OBJECT-TYPE
			SYNTAX	INTEGER
			MAX-ACCESS	read-only
			STATUS	current
			::= { hmWanMbusDE 82 }

hmWanMbusDEValue26		OBJECT-TYPE
			SYNTAX	INTEGER
			MAX-ACCESS	read-only
			STATUS	current
			::= { hmWanMbusDE 83 }

hmWanMbusDEVIF27		OBJECT-TYPE
			SYNTAX	INTEGER
			MAX-ACCESS	read-only
			STATUS	current
			::= { hmWanMbusDE 84 }

hmWanMbusDEValue27		OBJECT-TYPE
			SYNTAX	INTEGER
			MAX-ACCESS	read-only
			STATUS	current
			::= { hmWanMbusDE 85 }

hmWanMbusDEVIF28		OBJECT-TYPE
			SYNTAX	INTEGER
			MAX-ACCESS	read-only
			STATUS	current
			::= { hmWanMbusDE 86 }

hmWanMbusDEValue28		OBJECT-TYPE
			SYNTAX	INTEGER
			MAX-ACCESS	read-only
			STATUS	current
			::= { hmWanMbusDE 87 }

hmWanMbusDEVIF29		OBJECT-TYPE
			SYNTAX	INTEGER
			MAX-ACCESS	read-only
			STATUS	current
			::= { hmWanMbusDE 88 }

hmWanMbusDEValue29		OBJECT-TYPE
			SYNTAX	INTEGER
			MAX-ACCESS	read-only
			STATUS	current
			::= { hmWanMbusDE 89 }

hmWanMbusDEVIF2A		OBJECT-TYPE
			SYNTAX	INTEGER
			MAX-ACCESS	read-only
			STATUS	current
			::= { hmWanMbusDE 90 }

hmWanMbusDEValue2A		OBJECT-TYPE
			SYNTAX	INTEGER
			MAX-ACCESS	read-only
			STATUS	current
			::= { hmWanMbusDE 91 }

hmWanMbusDEVIF2B		OBJECT-TYPE
			SYNTAX	INTEGER
			MAX-ACCESS	read-only
			STATUS	current
			::= { hmWanMbusDE 92 }

hmWanMbusDEValue2B		OBJECT-TYPE
			SYNTAX	INTEGER
			MAX-ACCESS	read-only
			STATUS	current
			::= { hmWanMbusDE 93 }

hmWanMbusDEVIF2C		OBJECT-TYPE
			SYNTAX	INTEGER
			MAX-ACCESS	read-only
			STATUS	current
			::= { hmWanMbusDE 94 }

hmWanMbusDEValue2C		OBJECT-TYPE
			SYNTAX	INTEGER
			MAX-ACCESS	read-only
			STATUS	current
			::= { hmWanMbusDE 95 }

hmWanMbusDEVIF2D		OBJECT-TYPE
			SYNTAX	INTEGER
			MAX-ACCESS	read-only
			STATUS	current
			::= { hmWanMbusDE 96 }

hmWanMbusDEValue2D		OBJECT-TYPE
			SYNTAX	INTEGER
			MAX-ACCESS	read-only
			STATUS	current
			::= { hmWanMbusDE 97 }

hmWanMbusDEVIF2E		OBJECT-TYPE
			SYNTAX	INTEGER
			MAX-ACCESS	read-only
			STATUS	current
			::= { hmWanMbusDE 98 }

hmWanMbusDEValue2E		OBJECT-TYPE
			SYNTAX	INTEGER
			MAX-ACCESS	read-only
			STATUS	current
			::= { hmWanMbusDE 99 }

hmWanMbusDEVIF2F		OBJECT-TYPE
			SYNTAX	INTEGER
			MAX-ACCESS	read-only
			STATUS	current
			::= { hmWanMbusDE 100 }

hmWanMbusDEValue2F		OBJECT-TYPE
			SYNTAX	INTEGER
			MAX-ACCESS	read-only
			STATUS	current
			::= { hmWanMbusDE 101 }

hmWanMbusDF			OBJECT IDENTIFIER ::= { hmWanMbus 223 }

hmWanMbusDFIdNumber		OBJECT-TYPE
			SYNTAX	Gauge32
			MAX-ACCESS	read-only
			STATUS	current
			::= { hmWanMbusDF 1 }

hmWanMbusDFManufacturer	OBJECT-TYPE
			SYNTAX	Gauge32
			MAX-ACCESS	read-only
			STATUS	current
			::= { hmWanMbusDF 2 }

hmWanMbusDFVersion		OBJECT-TYPE
			SYNTAX	Gauge32
			MAX-ACCESS	read-only
			STATUS	current
			::= { hmWanMbusDF 3 }

hmWanMbusDFMedium		OBJECT-TYPE
			SYNTAX	Gauge32
			MAX-ACCESS	read-only
			STATUS	current
			::= { hmWanMbusDF 4 }

hmWanMbusDFStatus		OBJECT-TYPE
			SYNTAX	Gauge32
			MAX-ACCESS	read-only
			STATUS	current
			::= { hmWanMbusDF 5 }

hmWanMbusDFVIF00		OBJECT-TYPE
			SYNTAX	INTEGER
			MAX-ACCESS	read-only
			STATUS	current
			::= { hmWanMbusDF 6 }

hmWanMbusDFValue00		OBJECT-TYPE
			SYNTAX	INTEGER
			MAX-ACCESS	read-only
			STATUS	current
			::= { hmWanMbusDF 7 }

hmWanMbusDFVIF01		OBJECT-TYPE
			SYNTAX	INTEGER
			MAX-ACCESS	read-only
			STATUS	current
			::= { hmWanMbusDF 8 }

hmWanMbusDFValue01		OBJECT-TYPE
			SYNTAX	INTEGER
			MAX-ACCESS	read-only
			STATUS	current
			::= { hmWanMbusDF 9 }

hmWanMbusDFVIF02		OBJECT-TYPE
			SYNTAX	INTEGER
			MAX-ACCESS	read-only
			STATUS	current
			::= { hmWanMbusDF 10 }

hmWanMbusDFValue02		OBJECT-TYPE
			SYNTAX	INTEGER
			MAX-ACCESS	read-only
			STATUS	current
			::= { hmWanMbusDF 11 }

hmWanMbusDFVIF03		OBJECT-TYPE
			SYNTAX	INTEGER
			MAX-ACCESS	read-only
			STATUS	current
			::= { hmWanMbusDF 12 }

hmWanMbusDFValue03		OBJECT-TYPE
			SYNTAX	INTEGER
			MAX-ACCESS	read-only
			STATUS	current
			::= { hmWanMbusDF 13 }

hmWanMbusDFVIF04		OBJECT-TYPE
			SYNTAX	INTEGER
			MAX-ACCESS	read-only
			STATUS	current
			::= { hmWanMbusDF 14 }

hmWanMbusDFValue04		OBJECT-TYPE
			SYNTAX	INTEGER
			MAX-ACCESS	read-only
			STATUS	current
			::= { hmWanMbusDF 15 }

hmWanMbusDFVIF05		OBJECT-TYPE
			SYNTAX	INTEGER
			MAX-ACCESS	read-only
			STATUS	current
			::= { hmWanMbusDF 16 }

hmWanMbusDFValue05		OBJECT-TYPE
			SYNTAX	INTEGER
			MAX-ACCESS	read-only
			STATUS	current
			::= { hmWanMbusDF 17 }

hmWanMbusDFVIF06		OBJECT-TYPE
			SYNTAX	INTEGER
			MAX-ACCESS	read-only
			STATUS	current
			::= { hmWanMbusDF 18 }

hmWanMbusDFValue06		OBJECT-TYPE
			SYNTAX	INTEGER
			MAX-ACCESS	read-only
			STATUS	current
			::= { hmWanMbusDF 19 }

hmWanMbusDFVIF07		OBJECT-TYPE
			SYNTAX	INTEGER
			MAX-ACCESS	read-only
			STATUS	current
			::= { hmWanMbusDF 20 }

hmWanMbusDFValue07		OBJECT-TYPE
			SYNTAX	INTEGER
			MAX-ACCESS	read-only
			STATUS	current
			::= { hmWanMbusDF 21 }

hmWanMbusDFVIF08		OBJECT-TYPE
			SYNTAX	INTEGER
			MAX-ACCESS	read-only
			STATUS	current
			::= { hmWanMbusDF 22 }

hmWanMbusDFValue08		OBJECT-TYPE
			SYNTAX	INTEGER
			MAX-ACCESS	read-only
			STATUS	current
			::= { hmWanMbusDF 23 }

hmWanMbusDFVIF09		OBJECT-TYPE
			SYNTAX	INTEGER
			MAX-ACCESS	read-only
			STATUS	current
			::= { hmWanMbusDF 24 }

hmWanMbusDFValue09		OBJECT-TYPE
			SYNTAX	INTEGER
			MAX-ACCESS	read-only
			STATUS	current
			::= { hmWanMbusDF 25 }

hmWanMbusDFVIF0A		OBJECT-TYPE
			SYNTAX	INTEGER
			MAX-ACCESS	read-only
			STATUS	current
			::= { hmWanMbusDF 26 }

hmWanMbusDFValue0A		OBJECT-TYPE
			SYNTAX	INTEGER
			MAX-ACCESS	read-only
			STATUS	current
			::= { hmWanMbusDF 27 }

hmWanMbusDFVIF0B		OBJECT-TYPE
			SYNTAX	INTEGER
			MAX-ACCESS	read-only
			STATUS	current
			::= { hmWanMbusDF 28 }

hmWanMbusDFValue0B		OBJECT-TYPE
			SYNTAX	INTEGER
			MAX-ACCESS	read-only
			STATUS	current
			::= { hmWanMbusDF 29 }

hmWanMbusDFVIF0C		OBJECT-TYPE
			SYNTAX	INTEGER
			MAX-ACCESS	read-only
			STATUS	current
			::= { hmWanMbusDF 30 }

hmWanMbusDFValue0C		OBJECT-TYPE
			SYNTAX	INTEGER
			MAX-ACCESS	read-only
			STATUS	current
			::= { hmWanMbusDF 31 }

hmWanMbusDFVIF0D		OBJECT-TYPE
			SYNTAX	INTEGER
			MAX-ACCESS	read-only
			STATUS	current
			::= { hmWanMbusDF 32 }

hmWanMbusDFValue0D		OBJECT-TYPE
			SYNTAX	INTEGER
			MAX-ACCESS	read-only
			STATUS	current
			::= { hmWanMbusDF 33 }

hmWanMbusDFVIF0E		OBJECT-TYPE
			SYNTAX	INTEGER
			MAX-ACCESS	read-only
			STATUS	current
			::= { hmWanMbusDF 34 }

hmWanMbusDFValue0E		OBJECT-TYPE
			SYNTAX	INTEGER
			MAX-ACCESS	read-only
			STATUS	current
			::= { hmWanMbusDF 35 }

hmWanMbusDFVIF0F		OBJECT-TYPE
			SYNTAX	INTEGER
			MAX-ACCESS	read-only
			STATUS	current
			::= { hmWanMbusDF 36 }

hmWanMbusDFValue0F		OBJECT-TYPE
			SYNTAX	INTEGER
			MAX-ACCESS	read-only
			STATUS	current
			::= { hmWanMbusDF 37 }

hmWanMbusDFVIF10		OBJECT-TYPE
			SYNTAX	INTEGER
			MAX-ACCESS	read-only
			STATUS	current
			::= { hmWanMbusDF 38 }

hmWanMbusDFValue10		OBJECT-TYPE
			SYNTAX	INTEGER
			MAX-ACCESS	read-only
			STATUS	current
			::= { hmWanMbusDF 39 }

hmWanMbusDFVIF11		OBJECT-TYPE
			SYNTAX	INTEGER
			MAX-ACCESS	read-only
			STATUS	current
			::= { hmWanMbusDF 40 }

hmWanMbusDFValue11		OBJECT-TYPE
			SYNTAX	INTEGER
			MAX-ACCESS	read-only
			STATUS	current
			::= { hmWanMbusDF 41 }

hmWanMbusDFVIF12		OBJECT-TYPE
			SYNTAX	INTEGER
			MAX-ACCESS	read-only
			STATUS	current
			::= { hmWanMbusDF 42 }

hmWanMbusDFValue12		OBJECT-TYPE
			SYNTAX	INTEGER
			MAX-ACCESS	read-only
			STATUS	current
			::= { hmWanMbusDF 43 }

hmWanMbusDFVIF13		OBJECT-TYPE
			SYNTAX	INTEGER
			MAX-ACCESS	read-only
			STATUS	current
			::= { hmWanMbusDF 44 }

hmWanMbusDFValue13		OBJECT-TYPE
			SYNTAX	INTEGER
			MAX-ACCESS	read-only
			STATUS	current
			::= { hmWanMbusDF 45 }

hmWanMbusDFVIF14		OBJECT-TYPE
			SYNTAX	INTEGER
			MAX-ACCESS	read-only
			STATUS	current
			::= { hmWanMbusDF 46 }

hmWanMbusDFValue14		OBJECT-TYPE
			SYNTAX	INTEGER
			MAX-ACCESS	read-only
			STATUS	current
			::= { hmWanMbusDF 47 }

hmWanMbusDFVIF15		OBJECT-TYPE
			SYNTAX	INTEGER
			MAX-ACCESS	read-only
			STATUS	current
			::= { hmWanMbusDF 48 }

hmWanMbusDFValue15		OBJECT-TYPE
			SYNTAX	INTEGER
			MAX-ACCESS	read-only
			STATUS	current
			::= { hmWanMbusDF 49 }

hmWanMbusDFVIF16		OBJECT-TYPE
			SYNTAX	INTEGER
			MAX-ACCESS	read-only
			STATUS	current
			::= { hmWanMbusDF 50 }

hmWanMbusDFValue16		OBJECT-TYPE
			SYNTAX	INTEGER
			MAX-ACCESS	read-only
			STATUS	current
			::= { hmWanMbusDF 51 }

hmWanMbusDFVIF17		OBJECT-TYPE
			SYNTAX	INTEGER
			MAX-ACCESS	read-only
			STATUS	current
			::= { hmWanMbusDF 52 }

hmWanMbusDFValue17		OBJECT-TYPE
			SYNTAX	INTEGER
			MAX-ACCESS	read-only
			STATUS	current
			::= { hmWanMbusDF 53 }

hmWanMbusDFVIF18		OBJECT-TYPE
			SYNTAX	INTEGER
			MAX-ACCESS	read-only
			STATUS	current
			::= { hmWanMbusDF 54 }

hmWanMbusDFValue18		OBJECT-TYPE
			SYNTAX	INTEGER
			MAX-ACCESS	read-only
			STATUS	current
			::= { hmWanMbusDF 55 }

hmWanMbusDFVIF19		OBJECT-TYPE
			SYNTAX	INTEGER
			MAX-ACCESS	read-only
			STATUS	current
			::= { hmWanMbusDF 56 }

hmWanMbusDFValue19		OBJECT-TYPE
			SYNTAX	INTEGER
			MAX-ACCESS	read-only
			STATUS	current
			::= { hmWanMbusDF 57 }

hmWanMbusDFVIF1A		OBJECT-TYPE
			SYNTAX	INTEGER
			MAX-ACCESS	read-only
			STATUS	current
			::= { hmWanMbusDF 58 }

hmWanMbusDFValue1A		OBJECT-TYPE
			SYNTAX	INTEGER
			MAX-ACCESS	read-only
			STATUS	current
			::= { hmWanMbusDF 59 }

hmWanMbusDFVIF1B		OBJECT-TYPE
			SYNTAX	INTEGER
			MAX-ACCESS	read-only
			STATUS	current
			::= { hmWanMbusDF 60 }

hmWanMbusDFValue1B		OBJECT-TYPE
			SYNTAX	INTEGER
			MAX-ACCESS	read-only
			STATUS	current
			::= { hmWanMbusDF 61 }

hmWanMbusDFVIF1C		OBJECT-TYPE
			SYNTAX	INTEGER
			MAX-ACCESS	read-only
			STATUS	current
			::= { hmWanMbusDF 62 }

hmWanMbusDFValue1C		OBJECT-TYPE
			SYNTAX	INTEGER
			MAX-ACCESS	read-only
			STATUS	current
			::= { hmWanMbusDF 63 }

hmWanMbusDFVIF1D		OBJECT-TYPE
			SYNTAX	INTEGER
			MAX-ACCESS	read-only
			STATUS	current
			::= { hmWanMbusDF 64 }

hmWanMbusDFValue1D		OBJECT-TYPE
			SYNTAX	INTEGER
			MAX-ACCESS	read-only
			STATUS	current
			::= { hmWanMbusDF 65 }

hmWanMbusDFVIF1E		OBJECT-TYPE
			SYNTAX	INTEGER
			MAX-ACCESS	read-only
			STATUS	current
			::= { hmWanMbusDF 66 }

hmWanMbusDFValue1E		OBJECT-TYPE
			SYNTAX	INTEGER
			MAX-ACCESS	read-only
			STATUS	current
			::= { hmWanMbusDF 67 }

hmWanMbusDFVIF1F		OBJECT-TYPE
			SYNTAX	INTEGER
			MAX-ACCESS	read-only
			STATUS	current
			::= { hmWanMbusDF 68 }

hmWanMbusDFValue1F		OBJECT-TYPE
			SYNTAX	INTEGER
			MAX-ACCESS	read-only
			STATUS	current
			::= { hmWanMbusDF 69 }

hmWanMbusDFVIF20		OBJECT-TYPE
			SYNTAX	INTEGER
			MAX-ACCESS	read-only
			STATUS	current
			::= { hmWanMbusDF 70 }

hmWanMbusDFValue20		OBJECT-TYPE
			SYNTAX	INTEGER
			MAX-ACCESS	read-only
			STATUS	current
			::= { hmWanMbusDF 71 }

hmWanMbusDFVIF21		OBJECT-TYPE
			SYNTAX	INTEGER
			MAX-ACCESS	read-only
			STATUS	current
			::= { hmWanMbusDF 72 }

hmWanMbusDFValue21		OBJECT-TYPE
			SYNTAX	INTEGER
			MAX-ACCESS	read-only
			STATUS	current
			::= { hmWanMbusDF 73 }

hmWanMbusDFVIF22		OBJECT-TYPE
			SYNTAX	INTEGER
			MAX-ACCESS	read-only
			STATUS	current
			::= { hmWanMbusDF 74 }

hmWanMbusDFValue22		OBJECT-TYPE
			SYNTAX	INTEGER
			MAX-ACCESS	read-only
			STATUS	current
			::= { hmWanMbusDF 75 }

hmWanMbusDFVIF23		OBJECT-TYPE
			SYNTAX	INTEGER
			MAX-ACCESS	read-only
			STATUS	current
			::= { hmWanMbusDF 76 }

hmWanMbusDFValue23		OBJECT-TYPE
			SYNTAX	INTEGER
			MAX-ACCESS	read-only
			STATUS	current
			::= { hmWanMbusDF 77 }

hmWanMbusDFVIF24		OBJECT-TYPE
			SYNTAX	INTEGER
			MAX-ACCESS	read-only
			STATUS	current
			::= { hmWanMbusDF 78 }

hmWanMbusDFValue24		OBJECT-TYPE
			SYNTAX	INTEGER
			MAX-ACCESS	read-only
			STATUS	current
			::= { hmWanMbusDF 79 }

hmWanMbusDFVIF25		OBJECT-TYPE
			SYNTAX	INTEGER
			MAX-ACCESS	read-only
			STATUS	current
			::= { hmWanMbusDF 80 }

hmWanMbusDFValue25		OBJECT-TYPE
			SYNTAX	INTEGER
			MAX-ACCESS	read-only
			STATUS	current
			::= { hmWanMbusDF 81 }

hmWanMbusDFVIF26		OBJECT-TYPE
			SYNTAX	INTEGER
			MAX-ACCESS	read-only
			STATUS	current
			::= { hmWanMbusDF 82 }

hmWanMbusDFValue26		OBJECT-TYPE
			SYNTAX	INTEGER
			MAX-ACCESS	read-only
			STATUS	current
			::= { hmWanMbusDF 83 }

hmWanMbusDFVIF27		OBJECT-TYPE
			SYNTAX	INTEGER
			MAX-ACCESS	read-only
			STATUS	current
			::= { hmWanMbusDF 84 }

hmWanMbusDFValue27		OBJECT-TYPE
			SYNTAX	INTEGER
			MAX-ACCESS	read-only
			STATUS	current
			::= { hmWanMbusDF 85 }

hmWanMbusDFVIF28		OBJECT-TYPE
			SYNTAX	INTEGER
			MAX-ACCESS	read-only
			STATUS	current
			::= { hmWanMbusDF 86 }

hmWanMbusDFValue28		OBJECT-TYPE
			SYNTAX	INTEGER
			MAX-ACCESS	read-only
			STATUS	current
			::= { hmWanMbusDF 87 }

hmWanMbusDFVIF29		OBJECT-TYPE
			SYNTAX	INTEGER
			MAX-ACCESS	read-only
			STATUS	current
			::= { hmWanMbusDF 88 }

hmWanMbusDFValue29		OBJECT-TYPE
			SYNTAX	INTEGER
			MAX-ACCESS	read-only
			STATUS	current
			::= { hmWanMbusDF 89 }

hmWanMbusDFVIF2A		OBJECT-TYPE
			SYNTAX	INTEGER
			MAX-ACCESS	read-only
			STATUS	current
			::= { hmWanMbusDF 90 }

hmWanMbusDFValue2A		OBJECT-TYPE
			SYNTAX	INTEGER
			MAX-ACCESS	read-only
			STATUS	current
			::= { hmWanMbusDF 91 }

hmWanMbusDFVIF2B		OBJECT-TYPE
			SYNTAX	INTEGER
			MAX-ACCESS	read-only
			STATUS	current
			::= { hmWanMbusDF 92 }

hmWanMbusDFValue2B		OBJECT-TYPE
			SYNTAX	INTEGER
			MAX-ACCESS	read-only
			STATUS	current
			::= { hmWanMbusDF 93 }

hmWanMbusDFVIF2C		OBJECT-TYPE
			SYNTAX	INTEGER
			MAX-ACCESS	read-only
			STATUS	current
			::= { hmWanMbusDF 94 }

hmWanMbusDFValue2C		OBJECT-TYPE
			SYNTAX	INTEGER
			MAX-ACCESS	read-only
			STATUS	current
			::= { hmWanMbusDF 95 }

hmWanMbusDFVIF2D		OBJECT-TYPE
			SYNTAX	INTEGER
			MAX-ACCESS	read-only
			STATUS	current
			::= { hmWanMbusDF 96 }

hmWanMbusDFValue2D		OBJECT-TYPE
			SYNTAX	INTEGER
			MAX-ACCESS	read-only
			STATUS	current
			::= { hmWanMbusDF 97 }

hmWanMbusDFVIF2E		OBJECT-TYPE
			SYNTAX	INTEGER
			MAX-ACCESS	read-only
			STATUS	current
			::= { hmWanMbusDF 98 }

hmWanMbusDFValue2E		OBJECT-TYPE
			SYNTAX	INTEGER
			MAX-ACCESS	read-only
			STATUS	current
			::= { hmWanMbusDF 99 }

hmWanMbusDFVIF2F		OBJECT-TYPE
			SYNTAX	INTEGER
			MAX-ACCESS	read-only
			STATUS	current
			::= { hmWanMbusDF 100 }

hmWanMbusDFValue2F		OBJECT-TYPE
			SYNTAX	INTEGER
			MAX-ACCESS	read-only
			STATUS	current
			::= { hmWanMbusDF 101 }

hmWanMbusE0			OBJECT IDENTIFIER ::= { hmWanMbus 224 }

hmWanMbusE0IdNumber		OBJECT-TYPE
			SYNTAX	Gauge32
			MAX-ACCESS	read-only
			STATUS	current
			::= { hmWanMbusE0 1 }

hmWanMbusE0Manufacturer	OBJECT-TYPE
			SYNTAX	Gauge32
			MAX-ACCESS	read-only
			STATUS	current
			::= { hmWanMbusE0 2 }

hmWanMbusE0Version		OBJECT-TYPE
			SYNTAX	Gauge32
			MAX-ACCESS	read-only
			STATUS	current
			::= { hmWanMbusE0 3 }

hmWanMbusE0Medium		OBJECT-TYPE
			SYNTAX	Gauge32
			MAX-ACCESS	read-only
			STATUS	current
			::= { hmWanMbusE0 4 }

hmWanMbusE0Status		OBJECT-TYPE
			SYNTAX	Gauge32
			MAX-ACCESS	read-only
			STATUS	current
			::= { hmWanMbusE0 5 }

hmWanMbusE0VIF00		OBJECT-TYPE
			SYNTAX	INTEGER
			MAX-ACCESS	read-only
			STATUS	current
			::= { hmWanMbusE0 6 }

hmWanMbusE0Value00		OBJECT-TYPE
			SYNTAX	INTEGER
			MAX-ACCESS	read-only
			STATUS	current
			::= { hmWanMbusE0 7 }

hmWanMbusE0VIF01		OBJECT-TYPE
			SYNTAX	INTEGER
			MAX-ACCESS	read-only
			STATUS	current
			::= { hmWanMbusE0 8 }

hmWanMbusE0Value01		OBJECT-TYPE
			SYNTAX	INTEGER
			MAX-ACCESS	read-only
			STATUS	current
			::= { hmWanMbusE0 9 }

hmWanMbusE0VIF02		OBJECT-TYPE
			SYNTAX	INTEGER
			MAX-ACCESS	read-only
			STATUS	current
			::= { hmWanMbusE0 10 }

hmWanMbusE0Value02		OBJECT-TYPE
			SYNTAX	INTEGER
			MAX-ACCESS	read-only
			STATUS	current
			::= { hmWanMbusE0 11 }

hmWanMbusE0VIF03		OBJECT-TYPE
			SYNTAX	INTEGER
			MAX-ACCESS	read-only
			STATUS	current
			::= { hmWanMbusE0 12 }

hmWanMbusE0Value03		OBJECT-TYPE
			SYNTAX	INTEGER
			MAX-ACCESS	read-only
			STATUS	current
			::= { hmWanMbusE0 13 }

hmWanMbusE0VIF04		OBJECT-TYPE
			SYNTAX	INTEGER
			MAX-ACCESS	read-only
			STATUS	current
			::= { hmWanMbusE0 14 }

hmWanMbusE0Value04		OBJECT-TYPE
			SYNTAX	INTEGER
			MAX-ACCESS	read-only
			STATUS	current
			::= { hmWanMbusE0 15 }

hmWanMbusE0VIF05		OBJECT-TYPE
			SYNTAX	INTEGER
			MAX-ACCESS	read-only
			STATUS	current
			::= { hmWanMbusE0 16 }

hmWanMbusE0Value05		OBJECT-TYPE
			SYNTAX	INTEGER
			MAX-ACCESS	read-only
			STATUS	current
			::= { hmWanMbusE0 17 }

hmWanMbusE0VIF06		OBJECT-TYPE
			SYNTAX	INTEGER
			MAX-ACCESS	read-only
			STATUS	current
			::= { hmWanMbusE0 18 }

hmWanMbusE0Value06		OBJECT-TYPE
			SYNTAX	INTEGER
			MAX-ACCESS	read-only
			STATUS	current
			::= { hmWanMbusE0 19 }

hmWanMbusE0VIF07		OBJECT-TYPE
			SYNTAX	INTEGER
			MAX-ACCESS	read-only
			STATUS	current
			::= { hmWanMbusE0 20 }

hmWanMbusE0Value07		OBJECT-TYPE
			SYNTAX	INTEGER
			MAX-ACCESS	read-only
			STATUS	current
			::= { hmWanMbusE0 21 }

hmWanMbusE0VIF08		OBJECT-TYPE
			SYNTAX	INTEGER
			MAX-ACCESS	read-only
			STATUS	current
			::= { hmWanMbusE0 22 }

hmWanMbusE0Value08		OBJECT-TYPE
			SYNTAX	INTEGER
			MAX-ACCESS	read-only
			STATUS	current
			::= { hmWanMbusE0 23 }

hmWanMbusE0VIF09		OBJECT-TYPE
			SYNTAX	INTEGER
			MAX-ACCESS	read-only
			STATUS	current
			::= { hmWanMbusE0 24 }

hmWanMbusE0Value09		OBJECT-TYPE
			SYNTAX	INTEGER
			MAX-ACCESS	read-only
			STATUS	current
			::= { hmWanMbusE0 25 }

hmWanMbusE0VIF0A		OBJECT-TYPE
			SYNTAX	INTEGER
			MAX-ACCESS	read-only
			STATUS	current
			::= { hmWanMbusE0 26 }

hmWanMbusE0Value0A		OBJECT-TYPE
			SYNTAX	INTEGER
			MAX-ACCESS	read-only
			STATUS	current
			::= { hmWanMbusE0 27 }

hmWanMbusE0VIF0B		OBJECT-TYPE
			SYNTAX	INTEGER
			MAX-ACCESS	read-only
			STATUS	current
			::= { hmWanMbusE0 28 }

hmWanMbusE0Value0B		OBJECT-TYPE
			SYNTAX	INTEGER
			MAX-ACCESS	read-only
			STATUS	current
			::= { hmWanMbusE0 29 }

hmWanMbusE0VIF0C		OBJECT-TYPE
			SYNTAX	INTEGER
			MAX-ACCESS	read-only
			STATUS	current
			::= { hmWanMbusE0 30 }

hmWanMbusE0Value0C		OBJECT-TYPE
			SYNTAX	INTEGER
			MAX-ACCESS	read-only
			STATUS	current
			::= { hmWanMbusE0 31 }

hmWanMbusE0VIF0D		OBJECT-TYPE
			SYNTAX	INTEGER
			MAX-ACCESS	read-only
			STATUS	current
			::= { hmWanMbusE0 32 }

hmWanMbusE0Value0D		OBJECT-TYPE
			SYNTAX	INTEGER
			MAX-ACCESS	read-only
			STATUS	current
			::= { hmWanMbusE0 33 }

hmWanMbusE0VIF0E		OBJECT-TYPE
			SYNTAX	INTEGER
			MAX-ACCESS	read-only
			STATUS	current
			::= { hmWanMbusE0 34 }

hmWanMbusE0Value0E		OBJECT-TYPE
			SYNTAX	INTEGER
			MAX-ACCESS	read-only
			STATUS	current
			::= { hmWanMbusE0 35 }

hmWanMbusE0VIF0F		OBJECT-TYPE
			SYNTAX	INTEGER
			MAX-ACCESS	read-only
			STATUS	current
			::= { hmWanMbusE0 36 }

hmWanMbusE0Value0F		OBJECT-TYPE
			SYNTAX	INTEGER
			MAX-ACCESS	read-only
			STATUS	current
			::= { hmWanMbusE0 37 }

hmWanMbusE0VIF10		OBJECT-TYPE
			SYNTAX	INTEGER
			MAX-ACCESS	read-only
			STATUS	current
			::= { hmWanMbusE0 38 }

hmWanMbusE0Value10		OBJECT-TYPE
			SYNTAX	INTEGER
			MAX-ACCESS	read-only
			STATUS	current
			::= { hmWanMbusE0 39 }

hmWanMbusE0VIF11		OBJECT-TYPE
			SYNTAX	INTEGER
			MAX-ACCESS	read-only
			STATUS	current
			::= { hmWanMbusE0 40 }

hmWanMbusE0Value11		OBJECT-TYPE
			SYNTAX	INTEGER
			MAX-ACCESS	read-only
			STATUS	current
			::= { hmWanMbusE0 41 }

hmWanMbusE0VIF12		OBJECT-TYPE
			SYNTAX	INTEGER
			MAX-ACCESS	read-only
			STATUS	current
			::= { hmWanMbusE0 42 }

hmWanMbusE0Value12		OBJECT-TYPE
			SYNTAX	INTEGER
			MAX-ACCESS	read-only
			STATUS	current
			::= { hmWanMbusE0 43 }

hmWanMbusE0VIF13		OBJECT-TYPE
			SYNTAX	INTEGER
			MAX-ACCESS	read-only
			STATUS	current
			::= { hmWanMbusE0 44 }

hmWanMbusE0Value13		OBJECT-TYPE
			SYNTAX	INTEGER
			MAX-ACCESS	read-only
			STATUS	current
			::= { hmWanMbusE0 45 }

hmWanMbusE0VIF14		OBJECT-TYPE
			SYNTAX	INTEGER
			MAX-ACCESS	read-only
			STATUS	current
			::= { hmWanMbusE0 46 }

hmWanMbusE0Value14		OBJECT-TYPE
			SYNTAX	INTEGER
			MAX-ACCESS	read-only
			STATUS	current
			::= { hmWanMbusE0 47 }

hmWanMbusE0VIF15		OBJECT-TYPE
			SYNTAX	INTEGER
			MAX-ACCESS	read-only
			STATUS	current
			::= { hmWanMbusE0 48 }

hmWanMbusE0Value15		OBJECT-TYPE
			SYNTAX	INTEGER
			MAX-ACCESS	read-only
			STATUS	current
			::= { hmWanMbusE0 49 }

hmWanMbusE0VIF16		OBJECT-TYPE
			SYNTAX	INTEGER
			MAX-ACCESS	read-only
			STATUS	current
			::= { hmWanMbusE0 50 }

hmWanMbusE0Value16		OBJECT-TYPE
			SYNTAX	INTEGER
			MAX-ACCESS	read-only
			STATUS	current
			::= { hmWanMbusE0 51 }

hmWanMbusE0VIF17		OBJECT-TYPE
			SYNTAX	INTEGER
			MAX-ACCESS	read-only
			STATUS	current
			::= { hmWanMbusE0 52 }

hmWanMbusE0Value17		OBJECT-TYPE
			SYNTAX	INTEGER
			MAX-ACCESS	read-only
			STATUS	current
			::= { hmWanMbusE0 53 }

hmWanMbusE0VIF18		OBJECT-TYPE
			SYNTAX	INTEGER
			MAX-ACCESS	read-only
			STATUS	current
			::= { hmWanMbusE0 54 }

hmWanMbusE0Value18		OBJECT-TYPE
			SYNTAX	INTEGER
			MAX-ACCESS	read-only
			STATUS	current
			::= { hmWanMbusE0 55 }

hmWanMbusE0VIF19		OBJECT-TYPE
			SYNTAX	INTEGER
			MAX-ACCESS	read-only
			STATUS	current
			::= { hmWanMbusE0 56 }

hmWanMbusE0Value19		OBJECT-TYPE
			SYNTAX	INTEGER
			MAX-ACCESS	read-only
			STATUS	current
			::= { hmWanMbusE0 57 }

hmWanMbusE0VIF1A		OBJECT-TYPE
			SYNTAX	INTEGER
			MAX-ACCESS	read-only
			STATUS	current
			::= { hmWanMbusE0 58 }

hmWanMbusE0Value1A		OBJECT-TYPE
			SYNTAX	INTEGER
			MAX-ACCESS	read-only
			STATUS	current
			::= { hmWanMbusE0 59 }

hmWanMbusE0VIF1B		OBJECT-TYPE
			SYNTAX	INTEGER
			MAX-ACCESS	read-only
			STATUS	current
			::= { hmWanMbusE0 60 }

hmWanMbusE0Value1B		OBJECT-TYPE
			SYNTAX	INTEGER
			MAX-ACCESS	read-only
			STATUS	current
			::= { hmWanMbusE0 61 }

hmWanMbusE0VIF1C		OBJECT-TYPE
			SYNTAX	INTEGER
			MAX-ACCESS	read-only
			STATUS	current
			::= { hmWanMbusE0 62 }

hmWanMbusE0Value1C		OBJECT-TYPE
			SYNTAX	INTEGER
			MAX-ACCESS	read-only
			STATUS	current
			::= { hmWanMbusE0 63 }

hmWanMbusE0VIF1D		OBJECT-TYPE
			SYNTAX	INTEGER
			MAX-ACCESS	read-only
			STATUS	current
			::= { hmWanMbusE0 64 }

hmWanMbusE0Value1D		OBJECT-TYPE
			SYNTAX	INTEGER
			MAX-ACCESS	read-only
			STATUS	current
			::= { hmWanMbusE0 65 }

hmWanMbusE0VIF1E		OBJECT-TYPE
			SYNTAX	INTEGER
			MAX-ACCESS	read-only
			STATUS	current
			::= { hmWanMbusE0 66 }

hmWanMbusE0Value1E		OBJECT-TYPE
			SYNTAX	INTEGER
			MAX-ACCESS	read-only
			STATUS	current
			::= { hmWanMbusE0 67 }

hmWanMbusE0VIF1F		OBJECT-TYPE
			SYNTAX	INTEGER
			MAX-ACCESS	read-only
			STATUS	current
			::= { hmWanMbusE0 68 }

hmWanMbusE0Value1F		OBJECT-TYPE
			SYNTAX	INTEGER
			MAX-ACCESS	read-only
			STATUS	current
			::= { hmWanMbusE0 69 }

hmWanMbusE0VIF20		OBJECT-TYPE
			SYNTAX	INTEGER
			MAX-ACCESS	read-only
			STATUS	current
			::= { hmWanMbusE0 70 }

hmWanMbusE0Value20		OBJECT-TYPE
			SYNTAX	INTEGER
			MAX-ACCESS	read-only
			STATUS	current
			::= { hmWanMbusE0 71 }

hmWanMbusE0VIF21		OBJECT-TYPE
			SYNTAX	INTEGER
			MAX-ACCESS	read-only
			STATUS	current
			::= { hmWanMbusE0 72 }

hmWanMbusE0Value21		OBJECT-TYPE
			SYNTAX	INTEGER
			MAX-ACCESS	read-only
			STATUS	current
			::= { hmWanMbusE0 73 }

hmWanMbusE0VIF22		OBJECT-TYPE
			SYNTAX	INTEGER
			MAX-ACCESS	read-only
			STATUS	current
			::= { hmWanMbusE0 74 }

hmWanMbusE0Value22		OBJECT-TYPE
			SYNTAX	INTEGER
			MAX-ACCESS	read-only
			STATUS	current
			::= { hmWanMbusE0 75 }

hmWanMbusE0VIF23		OBJECT-TYPE
			SYNTAX	INTEGER
			MAX-ACCESS	read-only
			STATUS	current
			::= { hmWanMbusE0 76 }

hmWanMbusE0Value23		OBJECT-TYPE
			SYNTAX	INTEGER
			MAX-ACCESS	read-only
			STATUS	current
			::= { hmWanMbusE0 77 }

hmWanMbusE0VIF24		OBJECT-TYPE
			SYNTAX	INTEGER
			MAX-ACCESS	read-only
			STATUS	current
			::= { hmWanMbusE0 78 }

hmWanMbusE0Value24		OBJECT-TYPE
			SYNTAX	INTEGER
			MAX-ACCESS	read-only
			STATUS	current
			::= { hmWanMbusE0 79 }

hmWanMbusE0VIF25		OBJECT-TYPE
			SYNTAX	INTEGER
			MAX-ACCESS	read-only
			STATUS	current
			::= { hmWanMbusE0 80 }

hmWanMbusE0Value25		OBJECT-TYPE
			SYNTAX	INTEGER
			MAX-ACCESS	read-only
			STATUS	current
			::= { hmWanMbusE0 81 }

hmWanMbusE0VIF26		OBJECT-TYPE
			SYNTAX	INTEGER
			MAX-ACCESS	read-only
			STATUS	current
			::= { hmWanMbusE0 82 }

hmWanMbusE0Value26		OBJECT-TYPE
			SYNTAX	INTEGER
			MAX-ACCESS	read-only
			STATUS	current
			::= { hmWanMbusE0 83 }

hmWanMbusE0VIF27		OBJECT-TYPE
			SYNTAX	INTEGER
			MAX-ACCESS	read-only
			STATUS	current
			::= { hmWanMbusE0 84 }

hmWanMbusE0Value27		OBJECT-TYPE
			SYNTAX	INTEGER
			MAX-ACCESS	read-only
			STATUS	current
			::= { hmWanMbusE0 85 }

hmWanMbusE0VIF28		OBJECT-TYPE
			SYNTAX	INTEGER
			MAX-ACCESS	read-only
			STATUS	current
			::= { hmWanMbusE0 86 }

hmWanMbusE0Value28		OBJECT-TYPE
			SYNTAX	INTEGER
			MAX-ACCESS	read-only
			STATUS	current
			::= { hmWanMbusE0 87 }

hmWanMbusE0VIF29		OBJECT-TYPE
			SYNTAX	INTEGER
			MAX-ACCESS	read-only
			STATUS	current
			::= { hmWanMbusE0 88 }

hmWanMbusE0Value29		OBJECT-TYPE
			SYNTAX	INTEGER
			MAX-ACCESS	read-only
			STATUS	current
			::= { hmWanMbusE0 89 }

hmWanMbusE0VIF2A		OBJECT-TYPE
			SYNTAX	INTEGER
			MAX-ACCESS	read-only
			STATUS	current
			::= { hmWanMbusE0 90 }

hmWanMbusE0Value2A		OBJECT-TYPE
			SYNTAX	INTEGER
			MAX-ACCESS	read-only
			STATUS	current
			::= { hmWanMbusE0 91 }

hmWanMbusE0VIF2B		OBJECT-TYPE
			SYNTAX	INTEGER
			MAX-ACCESS	read-only
			STATUS	current
			::= { hmWanMbusE0 92 }

hmWanMbusE0Value2B		OBJECT-TYPE
			SYNTAX	INTEGER
			MAX-ACCESS	read-only
			STATUS	current
			::= { hmWanMbusE0 93 }

hmWanMbusE0VIF2C		OBJECT-TYPE
			SYNTAX	INTEGER
			MAX-ACCESS	read-only
			STATUS	current
			::= { hmWanMbusE0 94 }

hmWanMbusE0Value2C		OBJECT-TYPE
			SYNTAX	INTEGER
			MAX-ACCESS	read-only
			STATUS	current
			::= { hmWanMbusE0 95 }

hmWanMbusE0VIF2D		OBJECT-TYPE
			SYNTAX	INTEGER
			MAX-ACCESS	read-only
			STATUS	current
			::= { hmWanMbusE0 96 }

hmWanMbusE0Value2D		OBJECT-TYPE
			SYNTAX	INTEGER
			MAX-ACCESS	read-only
			STATUS	current
			::= { hmWanMbusE0 97 }

hmWanMbusE0VIF2E		OBJECT-TYPE
			SYNTAX	INTEGER
			MAX-ACCESS	read-only
			STATUS	current
			::= { hmWanMbusE0 98 }

hmWanMbusE0Value2E		OBJECT-TYPE
			SYNTAX	INTEGER
			MAX-ACCESS	read-only
			STATUS	current
			::= { hmWanMbusE0 99 }

hmWanMbusE0VIF2F		OBJECT-TYPE
			SYNTAX	INTEGER
			MAX-ACCESS	read-only
			STATUS	current
			::= { hmWanMbusE0 100 }

hmWanMbusE0Value2F		OBJECT-TYPE
			SYNTAX	INTEGER
			MAX-ACCESS	read-only
			STATUS	current
			::= { hmWanMbusE0 101 }

hmWanMbusE1			OBJECT IDENTIFIER ::= { hmWanMbus 225 }

hmWanMbusE1IdNumber		OBJECT-TYPE
			SYNTAX	Gauge32
			MAX-ACCESS	read-only
			STATUS	current
			::= { hmWanMbusE1 1 }

hmWanMbusE1Manufacturer	OBJECT-TYPE
			SYNTAX	Gauge32
			MAX-ACCESS	read-only
			STATUS	current
			::= { hmWanMbusE1 2 }

hmWanMbusE1Version		OBJECT-TYPE
			SYNTAX	Gauge32
			MAX-ACCESS	read-only
			STATUS	current
			::= { hmWanMbusE1 3 }

hmWanMbusE1Medium		OBJECT-TYPE
			SYNTAX	Gauge32
			MAX-ACCESS	read-only
			STATUS	current
			::= { hmWanMbusE1 4 }

hmWanMbusE1Status		OBJECT-TYPE
			SYNTAX	Gauge32
			MAX-ACCESS	read-only
			STATUS	current
			::= { hmWanMbusE1 5 }

hmWanMbusE1VIF00		OBJECT-TYPE
			SYNTAX	INTEGER
			MAX-ACCESS	read-only
			STATUS	current
			::= { hmWanMbusE1 6 }

hmWanMbusE1Value00		OBJECT-TYPE
			SYNTAX	INTEGER
			MAX-ACCESS	read-only
			STATUS	current
			::= { hmWanMbusE1 7 }

hmWanMbusE1VIF01		OBJECT-TYPE
			SYNTAX	INTEGER
			MAX-ACCESS	read-only
			STATUS	current
			::= { hmWanMbusE1 8 }

hmWanMbusE1Value01		OBJECT-TYPE
			SYNTAX	INTEGER
			MAX-ACCESS	read-only
			STATUS	current
			::= { hmWanMbusE1 9 }

hmWanMbusE1VIF02		OBJECT-TYPE
			SYNTAX	INTEGER
			MAX-ACCESS	read-only
			STATUS	current
			::= { hmWanMbusE1 10 }

hmWanMbusE1Value02		OBJECT-TYPE
			SYNTAX	INTEGER
			MAX-ACCESS	read-only
			STATUS	current
			::= { hmWanMbusE1 11 }

hmWanMbusE1VIF03		OBJECT-TYPE
			SYNTAX	INTEGER
			MAX-ACCESS	read-only
			STATUS	current
			::= { hmWanMbusE1 12 }

hmWanMbusE1Value03		OBJECT-TYPE
			SYNTAX	INTEGER
			MAX-ACCESS	read-only
			STATUS	current
			::= { hmWanMbusE1 13 }

hmWanMbusE1VIF04		OBJECT-TYPE
			SYNTAX	INTEGER
			MAX-ACCESS	read-only
			STATUS	current
			::= { hmWanMbusE1 14 }

hmWanMbusE1Value04		OBJECT-TYPE
			SYNTAX	INTEGER
			MAX-ACCESS	read-only
			STATUS	current
			::= { hmWanMbusE1 15 }

hmWanMbusE1VIF05		OBJECT-TYPE
			SYNTAX	INTEGER
			MAX-ACCESS	read-only
			STATUS	current
			::= { hmWanMbusE1 16 }

hmWanMbusE1Value05		OBJECT-TYPE
			SYNTAX	INTEGER
			MAX-ACCESS	read-only
			STATUS	current
			::= { hmWanMbusE1 17 }

hmWanMbusE1VIF06		OBJECT-TYPE
			SYNTAX	INTEGER
			MAX-ACCESS	read-only
			STATUS	current
			::= { hmWanMbusE1 18 }

hmWanMbusE1Value06		OBJECT-TYPE
			SYNTAX	INTEGER
			MAX-ACCESS	read-only
			STATUS	current
			::= { hmWanMbusE1 19 }

hmWanMbusE1VIF07		OBJECT-TYPE
			SYNTAX	INTEGER
			MAX-ACCESS	read-only
			STATUS	current
			::= { hmWanMbusE1 20 }

hmWanMbusE1Value07		OBJECT-TYPE
			SYNTAX	INTEGER
			MAX-ACCESS	read-only
			STATUS	current
			::= { hmWanMbusE1 21 }

hmWanMbusE1VIF08		OBJECT-TYPE
			SYNTAX	INTEGER
			MAX-ACCESS	read-only
			STATUS	current
			::= { hmWanMbusE1 22 }

hmWanMbusE1Value08		OBJECT-TYPE
			SYNTAX	INTEGER
			MAX-ACCESS	read-only
			STATUS	current
			::= { hmWanMbusE1 23 }

hmWanMbusE1VIF09		OBJECT-TYPE
			SYNTAX	INTEGER
			MAX-ACCESS	read-only
			STATUS	current
			::= { hmWanMbusE1 24 }

hmWanMbusE1Value09		OBJECT-TYPE
			SYNTAX	INTEGER
			MAX-ACCESS	read-only
			STATUS	current
			::= { hmWanMbusE1 25 }

hmWanMbusE1VIF0A		OBJECT-TYPE
			SYNTAX	INTEGER
			MAX-ACCESS	read-only
			STATUS	current
			::= { hmWanMbusE1 26 }

hmWanMbusE1Value0A		OBJECT-TYPE
			SYNTAX	INTEGER
			MAX-ACCESS	read-only
			STATUS	current
			::= { hmWanMbusE1 27 }

hmWanMbusE1VIF0B		OBJECT-TYPE
			SYNTAX	INTEGER
			MAX-ACCESS	read-only
			STATUS	current
			::= { hmWanMbusE1 28 }

hmWanMbusE1Value0B		OBJECT-TYPE
			SYNTAX	INTEGER
			MAX-ACCESS	read-only
			STATUS	current
			::= { hmWanMbusE1 29 }

hmWanMbusE1VIF0C		OBJECT-TYPE
			SYNTAX	INTEGER
			MAX-ACCESS	read-only
			STATUS	current
			::= { hmWanMbusE1 30 }

hmWanMbusE1Value0C		OBJECT-TYPE
			SYNTAX	INTEGER
			MAX-ACCESS	read-only
			STATUS	current
			::= { hmWanMbusE1 31 }

hmWanMbusE1VIF0D		OBJECT-TYPE
			SYNTAX	INTEGER
			MAX-ACCESS	read-only
			STATUS	current
			::= { hmWanMbusE1 32 }

hmWanMbusE1Value0D		OBJECT-TYPE
			SYNTAX	INTEGER
			MAX-ACCESS	read-only
			STATUS	current
			::= { hmWanMbusE1 33 }

hmWanMbusE1VIF0E		OBJECT-TYPE
			SYNTAX	INTEGER
			MAX-ACCESS	read-only
			STATUS	current
			::= { hmWanMbusE1 34 }

hmWanMbusE1Value0E		OBJECT-TYPE
			SYNTAX	INTEGER
			MAX-ACCESS	read-only
			STATUS	current
			::= { hmWanMbusE1 35 }

hmWanMbusE1VIF0F		OBJECT-TYPE
			SYNTAX	INTEGER
			MAX-ACCESS	read-only
			STATUS	current
			::= { hmWanMbusE1 36 }

hmWanMbusE1Value0F		OBJECT-TYPE
			SYNTAX	INTEGER
			MAX-ACCESS	read-only
			STATUS	current
			::= { hmWanMbusE1 37 }

hmWanMbusE1VIF10		OBJECT-TYPE
			SYNTAX	INTEGER
			MAX-ACCESS	read-only
			STATUS	current
			::= { hmWanMbusE1 38 }

hmWanMbusE1Value10		OBJECT-TYPE
			SYNTAX	INTEGER
			MAX-ACCESS	read-only
			STATUS	current
			::= { hmWanMbusE1 39 }

hmWanMbusE1VIF11		OBJECT-TYPE
			SYNTAX	INTEGER
			MAX-ACCESS	read-only
			STATUS	current
			::= { hmWanMbusE1 40 }

hmWanMbusE1Value11		OBJECT-TYPE
			SYNTAX	INTEGER
			MAX-ACCESS	read-only
			STATUS	current
			::= { hmWanMbusE1 41 }

hmWanMbusE1VIF12		OBJECT-TYPE
			SYNTAX	INTEGER
			MAX-ACCESS	read-only
			STATUS	current
			::= { hmWanMbusE1 42 }

hmWanMbusE1Value12		OBJECT-TYPE
			SYNTAX	INTEGER
			MAX-ACCESS	read-only
			STATUS	current
			::= { hmWanMbusE1 43 }

hmWanMbusE1VIF13		OBJECT-TYPE
			SYNTAX	INTEGER
			MAX-ACCESS	read-only
			STATUS	current
			::= { hmWanMbusE1 44 }

hmWanMbusE1Value13		OBJECT-TYPE
			SYNTAX	INTEGER
			MAX-ACCESS	read-only
			STATUS	current
			::= { hmWanMbusE1 45 }

hmWanMbusE1VIF14		OBJECT-TYPE
			SYNTAX	INTEGER
			MAX-ACCESS	read-only
			STATUS	current
			::= { hmWanMbusE1 46 }

hmWanMbusE1Value14		OBJECT-TYPE
			SYNTAX	INTEGER
			MAX-ACCESS	read-only
			STATUS	current
			::= { hmWanMbusE1 47 }

hmWanMbusE1VIF15		OBJECT-TYPE
			SYNTAX	INTEGER
			MAX-ACCESS	read-only
			STATUS	current
			::= { hmWanMbusE1 48 }

hmWanMbusE1Value15		OBJECT-TYPE
			SYNTAX	INTEGER
			MAX-ACCESS	read-only
			STATUS	current
			::= { hmWanMbusE1 49 }

hmWanMbusE1VIF16		OBJECT-TYPE
			SYNTAX	INTEGER
			MAX-ACCESS	read-only
			STATUS	current
			::= { hmWanMbusE1 50 }

hmWanMbusE1Value16		OBJECT-TYPE
			SYNTAX	INTEGER
			MAX-ACCESS	read-only
			STATUS	current
			::= { hmWanMbusE1 51 }

hmWanMbusE1VIF17		OBJECT-TYPE
			SYNTAX	INTEGER
			MAX-ACCESS	read-only
			STATUS	current
			::= { hmWanMbusE1 52 }

hmWanMbusE1Value17		OBJECT-TYPE
			SYNTAX	INTEGER
			MAX-ACCESS	read-only
			STATUS	current
			::= { hmWanMbusE1 53 }

hmWanMbusE1VIF18		OBJECT-TYPE
			SYNTAX	INTEGER
			MAX-ACCESS	read-only
			STATUS	current
			::= { hmWanMbusE1 54 }

hmWanMbusE1Value18		OBJECT-TYPE
			SYNTAX	INTEGER
			MAX-ACCESS	read-only
			STATUS	current
			::= { hmWanMbusE1 55 }

hmWanMbusE1VIF19		OBJECT-TYPE
			SYNTAX	INTEGER
			MAX-ACCESS	read-only
			STATUS	current
			::= { hmWanMbusE1 56 }

hmWanMbusE1Value19		OBJECT-TYPE
			SYNTAX	INTEGER
			MAX-ACCESS	read-only
			STATUS	current
			::= { hmWanMbusE1 57 }

hmWanMbusE1VIF1A		OBJECT-TYPE
			SYNTAX	INTEGER
			MAX-ACCESS	read-only
			STATUS	current
			::= { hmWanMbusE1 58 }

hmWanMbusE1Value1A		OBJECT-TYPE
			SYNTAX	INTEGER
			MAX-ACCESS	read-only
			STATUS	current
			::= { hmWanMbusE1 59 }

hmWanMbusE1VIF1B		OBJECT-TYPE
			SYNTAX	INTEGER
			MAX-ACCESS	read-only
			STATUS	current
			::= { hmWanMbusE1 60 }

hmWanMbusE1Value1B		OBJECT-TYPE
			SYNTAX	INTEGER
			MAX-ACCESS	read-only
			STATUS	current
			::= { hmWanMbusE1 61 }

hmWanMbusE1VIF1C		OBJECT-TYPE
			SYNTAX	INTEGER
			MAX-ACCESS	read-only
			STATUS	current
			::= { hmWanMbusE1 62 }

hmWanMbusE1Value1C		OBJECT-TYPE
			SYNTAX	INTEGER
			MAX-ACCESS	read-only
			STATUS	current
			::= { hmWanMbusE1 63 }

hmWanMbusE1VIF1D		OBJECT-TYPE
			SYNTAX	INTEGER
			MAX-ACCESS	read-only
			STATUS	current
			::= { hmWanMbusE1 64 }

hmWanMbusE1Value1D		OBJECT-TYPE
			SYNTAX	INTEGER
			MAX-ACCESS	read-only
			STATUS	current
			::= { hmWanMbusE1 65 }

hmWanMbusE1VIF1E		OBJECT-TYPE
			SYNTAX	INTEGER
			MAX-ACCESS	read-only
			STATUS	current
			::= { hmWanMbusE1 66 }

hmWanMbusE1Value1E		OBJECT-TYPE
			SYNTAX	INTEGER
			MAX-ACCESS	read-only
			STATUS	current
			::= { hmWanMbusE1 67 }

hmWanMbusE1VIF1F		OBJECT-TYPE
			SYNTAX	INTEGER
			MAX-ACCESS	read-only
			STATUS	current
			::= { hmWanMbusE1 68 }

hmWanMbusE1Value1F		OBJECT-TYPE
			SYNTAX	INTEGER
			MAX-ACCESS	read-only
			STATUS	current
			::= { hmWanMbusE1 69 }

hmWanMbusE1VIF20		OBJECT-TYPE
			SYNTAX	INTEGER
			MAX-ACCESS	read-only
			STATUS	current
			::= { hmWanMbusE1 70 }

hmWanMbusE1Value20		OBJECT-TYPE
			SYNTAX	INTEGER
			MAX-ACCESS	read-only
			STATUS	current
			::= { hmWanMbusE1 71 }

hmWanMbusE1VIF21		OBJECT-TYPE
			SYNTAX	INTEGER
			MAX-ACCESS	read-only
			STATUS	current
			::= { hmWanMbusE1 72 }

hmWanMbusE1Value21		OBJECT-TYPE
			SYNTAX	INTEGER
			MAX-ACCESS	read-only
			STATUS	current
			::= { hmWanMbusE1 73 }

hmWanMbusE1VIF22		OBJECT-TYPE
			SYNTAX	INTEGER
			MAX-ACCESS	read-only
			STATUS	current
			::= { hmWanMbusE1 74 }

hmWanMbusE1Value22		OBJECT-TYPE
			SYNTAX	INTEGER
			MAX-ACCESS	read-only
			STATUS	current
			::= { hmWanMbusE1 75 }

hmWanMbusE1VIF23		OBJECT-TYPE
			SYNTAX	INTEGER
			MAX-ACCESS	read-only
			STATUS	current
			::= { hmWanMbusE1 76 }

hmWanMbusE1Value23		OBJECT-TYPE
			SYNTAX	INTEGER
			MAX-ACCESS	read-only
			STATUS	current
			::= { hmWanMbusE1 77 }

hmWanMbusE1VIF24		OBJECT-TYPE
			SYNTAX	INTEGER
			MAX-ACCESS	read-only
			STATUS	current
			::= { hmWanMbusE1 78 }

hmWanMbusE1Value24		OBJECT-TYPE
			SYNTAX	INTEGER
			MAX-ACCESS	read-only
			STATUS	current
			::= { hmWanMbusE1 79 }

hmWanMbusE1VIF25		OBJECT-TYPE
			SYNTAX	INTEGER
			MAX-ACCESS	read-only
			STATUS	current
			::= { hmWanMbusE1 80 }

hmWanMbusE1Value25		OBJECT-TYPE
			SYNTAX	INTEGER
			MAX-ACCESS	read-only
			STATUS	current
			::= { hmWanMbusE1 81 }

hmWanMbusE1VIF26		OBJECT-TYPE
			SYNTAX	INTEGER
			MAX-ACCESS	read-only
			STATUS	current
			::= { hmWanMbusE1 82 }

hmWanMbusE1Value26		OBJECT-TYPE
			SYNTAX	INTEGER
			MAX-ACCESS	read-only
			STATUS	current
			::= { hmWanMbusE1 83 }

hmWanMbusE1VIF27		OBJECT-TYPE
			SYNTAX	INTEGER
			MAX-ACCESS	read-only
			STATUS	current
			::= { hmWanMbusE1 84 }

hmWanMbusE1Value27		OBJECT-TYPE
			SYNTAX	INTEGER
			MAX-ACCESS	read-only
			STATUS	current
			::= { hmWanMbusE1 85 }

hmWanMbusE1VIF28		OBJECT-TYPE
			SYNTAX	INTEGER
			MAX-ACCESS	read-only
			STATUS	current
			::= { hmWanMbusE1 86 }

hmWanMbusE1Value28		OBJECT-TYPE
			SYNTAX	INTEGER
			MAX-ACCESS	read-only
			STATUS	current
			::= { hmWanMbusE1 87 }

hmWanMbusE1VIF29		OBJECT-TYPE
			SYNTAX	INTEGER
			MAX-ACCESS	read-only
			STATUS	current
			::= { hmWanMbusE1 88 }

hmWanMbusE1Value29		OBJECT-TYPE
			SYNTAX	INTEGER
			MAX-ACCESS	read-only
			STATUS	current
			::= { hmWanMbusE1 89 }

hmWanMbusE1VIF2A		OBJECT-TYPE
			SYNTAX	INTEGER
			MAX-ACCESS	read-only
			STATUS	current
			::= { hmWanMbusE1 90 }

hmWanMbusE1Value2A		OBJECT-TYPE
			SYNTAX	INTEGER
			MAX-ACCESS	read-only
			STATUS	current
			::= { hmWanMbusE1 91 }

hmWanMbusE1VIF2B		OBJECT-TYPE
			SYNTAX	INTEGER
			MAX-ACCESS	read-only
			STATUS	current
			::= { hmWanMbusE1 92 }

hmWanMbusE1Value2B		OBJECT-TYPE
			SYNTAX	INTEGER
			MAX-ACCESS	read-only
			STATUS	current
			::= { hmWanMbusE1 93 }

hmWanMbusE1VIF2C		OBJECT-TYPE
			SYNTAX	INTEGER
			MAX-ACCESS	read-only
			STATUS	current
			::= { hmWanMbusE1 94 }

hmWanMbusE1Value2C		OBJECT-TYPE
			SYNTAX	INTEGER
			MAX-ACCESS	read-only
			STATUS	current
			::= { hmWanMbusE1 95 }

hmWanMbusE1VIF2D		OBJECT-TYPE
			SYNTAX	INTEGER
			MAX-ACCESS	read-only
			STATUS	current
			::= { hmWanMbusE1 96 }

hmWanMbusE1Value2D		OBJECT-TYPE
			SYNTAX	INTEGER
			MAX-ACCESS	read-only
			STATUS	current
			::= { hmWanMbusE1 97 }

hmWanMbusE1VIF2E		OBJECT-TYPE
			SYNTAX	INTEGER
			MAX-ACCESS	read-only
			STATUS	current
			::= { hmWanMbusE1 98 }

hmWanMbusE1Value2E		OBJECT-TYPE
			SYNTAX	INTEGER
			MAX-ACCESS	read-only
			STATUS	current
			::= { hmWanMbusE1 99 }

hmWanMbusE1VIF2F		OBJECT-TYPE
			SYNTAX	INTEGER
			MAX-ACCESS	read-only
			STATUS	current
			::= { hmWanMbusE1 100 }

hmWanMbusE1Value2F		OBJECT-TYPE
			SYNTAX	INTEGER
			MAX-ACCESS	read-only
			STATUS	current
			::= { hmWanMbusE1 101 }

hmWanMbusE2			OBJECT IDENTIFIER ::= { hmWanMbus 226 }

hmWanMbusE2IdNumber		OBJECT-TYPE
			SYNTAX	Gauge32
			MAX-ACCESS	read-only
			STATUS	current
			::= { hmWanMbusE2 1 }

hmWanMbusE2Manufacturer	OBJECT-TYPE
			SYNTAX	Gauge32
			MAX-ACCESS	read-only
			STATUS	current
			::= { hmWanMbusE2 2 }

hmWanMbusE2Version		OBJECT-TYPE
			SYNTAX	Gauge32
			MAX-ACCESS	read-only
			STATUS	current
			::= { hmWanMbusE2 3 }

hmWanMbusE2Medium		OBJECT-TYPE
			SYNTAX	Gauge32
			MAX-ACCESS	read-only
			STATUS	current
			::= { hmWanMbusE2 4 }

hmWanMbusE2Status		OBJECT-TYPE
			SYNTAX	Gauge32
			MAX-ACCESS	read-only
			STATUS	current
			::= { hmWanMbusE2 5 }

hmWanMbusE2VIF00		OBJECT-TYPE
			SYNTAX	INTEGER
			MAX-ACCESS	read-only
			STATUS	current
			::= { hmWanMbusE2 6 }

hmWanMbusE2Value00		OBJECT-TYPE
			SYNTAX	INTEGER
			MAX-ACCESS	read-only
			STATUS	current
			::= { hmWanMbusE2 7 }

hmWanMbusE2VIF01		OBJECT-TYPE
			SYNTAX	INTEGER
			MAX-ACCESS	read-only
			STATUS	current
			::= { hmWanMbusE2 8 }

hmWanMbusE2Value01		OBJECT-TYPE
			SYNTAX	INTEGER
			MAX-ACCESS	read-only
			STATUS	current
			::= { hmWanMbusE2 9 }

hmWanMbusE2VIF02		OBJECT-TYPE
			SYNTAX	INTEGER
			MAX-ACCESS	read-only
			STATUS	current
			::= { hmWanMbusE2 10 }

hmWanMbusE2Value02		OBJECT-TYPE
			SYNTAX	INTEGER
			MAX-ACCESS	read-only
			STATUS	current
			::= { hmWanMbusE2 11 }

hmWanMbusE2VIF03		OBJECT-TYPE
			SYNTAX	INTEGER
			MAX-ACCESS	read-only
			STATUS	current
			::= { hmWanMbusE2 12 }

hmWanMbusE2Value03		OBJECT-TYPE
			SYNTAX	INTEGER
			MAX-ACCESS	read-only
			STATUS	current
			::= { hmWanMbusE2 13 }

hmWanMbusE2VIF04		OBJECT-TYPE
			SYNTAX	INTEGER
			MAX-ACCESS	read-only
			STATUS	current
			::= { hmWanMbusE2 14 }

hmWanMbusE2Value04		OBJECT-TYPE
			SYNTAX	INTEGER
			MAX-ACCESS	read-only
			STATUS	current
			::= { hmWanMbusE2 15 }

hmWanMbusE2VIF05		OBJECT-TYPE
			SYNTAX	INTEGER
			MAX-ACCESS	read-only
			STATUS	current
			::= { hmWanMbusE2 16 }

hmWanMbusE2Value05		OBJECT-TYPE
			SYNTAX	INTEGER
			MAX-ACCESS	read-only
			STATUS	current
			::= { hmWanMbusE2 17 }

hmWanMbusE2VIF06		OBJECT-TYPE
			SYNTAX	INTEGER
			MAX-ACCESS	read-only
			STATUS	current
			::= { hmWanMbusE2 18 }

hmWanMbusE2Value06		OBJECT-TYPE
			SYNTAX	INTEGER
			MAX-ACCESS	read-only
			STATUS	current
			::= { hmWanMbusE2 19 }

hmWanMbusE2VIF07		OBJECT-TYPE
			SYNTAX	INTEGER
			MAX-ACCESS	read-only
			STATUS	current
			::= { hmWanMbusE2 20 }

hmWanMbusE2Value07		OBJECT-TYPE
			SYNTAX	INTEGER
			MAX-ACCESS	read-only
			STATUS	current
			::= { hmWanMbusE2 21 }

hmWanMbusE2VIF08		OBJECT-TYPE
			SYNTAX	INTEGER
			MAX-ACCESS	read-only
			STATUS	current
			::= { hmWanMbusE2 22 }

hmWanMbusE2Value08		OBJECT-TYPE
			SYNTAX	INTEGER
			MAX-ACCESS	read-only
			STATUS	current
			::= { hmWanMbusE2 23 }

hmWanMbusE2VIF09		OBJECT-TYPE
			SYNTAX	INTEGER
			MAX-ACCESS	read-only
			STATUS	current
			::= { hmWanMbusE2 24 }

hmWanMbusE2Value09		OBJECT-TYPE
			SYNTAX	INTEGER
			MAX-ACCESS	read-only
			STATUS	current
			::= { hmWanMbusE2 25 }

hmWanMbusE2VIF0A		OBJECT-TYPE
			SYNTAX	INTEGER
			MAX-ACCESS	read-only
			STATUS	current
			::= { hmWanMbusE2 26 }

hmWanMbusE2Value0A		OBJECT-TYPE
			SYNTAX	INTEGER
			MAX-ACCESS	read-only
			STATUS	current
			::= { hmWanMbusE2 27 }

hmWanMbusE2VIF0B		OBJECT-TYPE
			SYNTAX	INTEGER
			MAX-ACCESS	read-only
			STATUS	current
			::= { hmWanMbusE2 28 }

hmWanMbusE2Value0B		OBJECT-TYPE
			SYNTAX	INTEGER
			MAX-ACCESS	read-only
			STATUS	current
			::= { hmWanMbusE2 29 }

hmWanMbusE2VIF0C		OBJECT-TYPE
			SYNTAX	INTEGER
			MAX-ACCESS	read-only
			STATUS	current
			::= { hmWanMbusE2 30 }

hmWanMbusE2Value0C		OBJECT-TYPE
			SYNTAX	INTEGER
			MAX-ACCESS	read-only
			STATUS	current
			::= { hmWanMbusE2 31 }

hmWanMbusE2VIF0D		OBJECT-TYPE
			SYNTAX	INTEGER
			MAX-ACCESS	read-only
			STATUS	current
			::= { hmWanMbusE2 32 }

hmWanMbusE2Value0D		OBJECT-TYPE
			SYNTAX	INTEGER
			MAX-ACCESS	read-only
			STATUS	current
			::= { hmWanMbusE2 33 }

hmWanMbusE2VIF0E		OBJECT-TYPE
			SYNTAX	INTEGER
			MAX-ACCESS	read-only
			STATUS	current
			::= { hmWanMbusE2 34 }

hmWanMbusE2Value0E		OBJECT-TYPE
			SYNTAX	INTEGER
			MAX-ACCESS	read-only
			STATUS	current
			::= { hmWanMbusE2 35 }

hmWanMbusE2VIF0F		OBJECT-TYPE
			SYNTAX	INTEGER
			MAX-ACCESS	read-only
			STATUS	current
			::= { hmWanMbusE2 36 }

hmWanMbusE2Value0F		OBJECT-TYPE
			SYNTAX	INTEGER
			MAX-ACCESS	read-only
			STATUS	current
			::= { hmWanMbusE2 37 }

hmWanMbusE2VIF10		OBJECT-TYPE
			SYNTAX	INTEGER
			MAX-ACCESS	read-only
			STATUS	current
			::= { hmWanMbusE2 38 }

hmWanMbusE2Value10		OBJECT-TYPE
			SYNTAX	INTEGER
			MAX-ACCESS	read-only
			STATUS	current
			::= { hmWanMbusE2 39 }

hmWanMbusE2VIF11		OBJECT-TYPE
			SYNTAX	INTEGER
			MAX-ACCESS	read-only
			STATUS	current
			::= { hmWanMbusE2 40 }

hmWanMbusE2Value11		OBJECT-TYPE
			SYNTAX	INTEGER
			MAX-ACCESS	read-only
			STATUS	current
			::= { hmWanMbusE2 41 }

hmWanMbusE2VIF12		OBJECT-TYPE
			SYNTAX	INTEGER
			MAX-ACCESS	read-only
			STATUS	current
			::= { hmWanMbusE2 42 }

hmWanMbusE2Value12		OBJECT-TYPE
			SYNTAX	INTEGER
			MAX-ACCESS	read-only
			STATUS	current
			::= { hmWanMbusE2 43 }

hmWanMbusE2VIF13		OBJECT-TYPE
			SYNTAX	INTEGER
			MAX-ACCESS	read-only
			STATUS	current
			::= { hmWanMbusE2 44 }

hmWanMbusE2Value13		OBJECT-TYPE
			SYNTAX	INTEGER
			MAX-ACCESS	read-only
			STATUS	current
			::= { hmWanMbusE2 45 }

hmWanMbusE2VIF14		OBJECT-TYPE
			SYNTAX	INTEGER
			MAX-ACCESS	read-only
			STATUS	current
			::= { hmWanMbusE2 46 }

hmWanMbusE2Value14		OBJECT-TYPE
			SYNTAX	INTEGER
			MAX-ACCESS	read-only
			STATUS	current
			::= { hmWanMbusE2 47 }

hmWanMbusE2VIF15		OBJECT-TYPE
			SYNTAX	INTEGER
			MAX-ACCESS	read-only
			STATUS	current
			::= { hmWanMbusE2 48 }

hmWanMbusE2Value15		OBJECT-TYPE
			SYNTAX	INTEGER
			MAX-ACCESS	read-only
			STATUS	current
			::= { hmWanMbusE2 49 }

hmWanMbusE2VIF16		OBJECT-TYPE
			SYNTAX	INTEGER
			MAX-ACCESS	read-only
			STATUS	current
			::= { hmWanMbusE2 50 }

hmWanMbusE2Value16		OBJECT-TYPE
			SYNTAX	INTEGER
			MAX-ACCESS	read-only
			STATUS	current
			::= { hmWanMbusE2 51 }

hmWanMbusE2VIF17		OBJECT-TYPE
			SYNTAX	INTEGER
			MAX-ACCESS	read-only
			STATUS	current
			::= { hmWanMbusE2 52 }

hmWanMbusE2Value17		OBJECT-TYPE
			SYNTAX	INTEGER
			MAX-ACCESS	read-only
			STATUS	current
			::= { hmWanMbusE2 53 }

hmWanMbusE2VIF18		OBJECT-TYPE
			SYNTAX	INTEGER
			MAX-ACCESS	read-only
			STATUS	current
			::= { hmWanMbusE2 54 }

hmWanMbusE2Value18		OBJECT-TYPE
			SYNTAX	INTEGER
			MAX-ACCESS	read-only
			STATUS	current
			::= { hmWanMbusE2 55 }

hmWanMbusE2VIF19		OBJECT-TYPE
			SYNTAX	INTEGER
			MAX-ACCESS	read-only
			STATUS	current
			::= { hmWanMbusE2 56 }

hmWanMbusE2Value19		OBJECT-TYPE
			SYNTAX	INTEGER
			MAX-ACCESS	read-only
			STATUS	current
			::= { hmWanMbusE2 57 }

hmWanMbusE2VIF1A		OBJECT-TYPE
			SYNTAX	INTEGER
			MAX-ACCESS	read-only
			STATUS	current
			::= { hmWanMbusE2 58 }

hmWanMbusE2Value1A		OBJECT-TYPE
			SYNTAX	INTEGER
			MAX-ACCESS	read-only
			STATUS	current
			::= { hmWanMbusE2 59 }

hmWanMbusE2VIF1B		OBJECT-TYPE
			SYNTAX	INTEGER
			MAX-ACCESS	read-only
			STATUS	current
			::= { hmWanMbusE2 60 }

hmWanMbusE2Value1B		OBJECT-TYPE
			SYNTAX	INTEGER
			MAX-ACCESS	read-only
			STATUS	current
			::= { hmWanMbusE2 61 }

hmWanMbusE2VIF1C		OBJECT-TYPE
			SYNTAX	INTEGER
			MAX-ACCESS	read-only
			STATUS	current
			::= { hmWanMbusE2 62 }

hmWanMbusE2Value1C		OBJECT-TYPE
			SYNTAX	INTEGER
			MAX-ACCESS	read-only
			STATUS	current
			::= { hmWanMbusE2 63 }

hmWanMbusE2VIF1D		OBJECT-TYPE
			SYNTAX	INTEGER
			MAX-ACCESS	read-only
			STATUS	current
			::= { hmWanMbusE2 64 }

hmWanMbusE2Value1D		OBJECT-TYPE
			SYNTAX	INTEGER
			MAX-ACCESS	read-only
			STATUS	current
			::= { hmWanMbusE2 65 }

hmWanMbusE2VIF1E		OBJECT-TYPE
			SYNTAX	INTEGER
			MAX-ACCESS	read-only
			STATUS	current
			::= { hmWanMbusE2 66 }

hmWanMbusE2Value1E		OBJECT-TYPE
			SYNTAX	INTEGER
			MAX-ACCESS	read-only
			STATUS	current
			::= { hmWanMbusE2 67 }

hmWanMbusE2VIF1F		OBJECT-TYPE
			SYNTAX	INTEGER
			MAX-ACCESS	read-only
			STATUS	current
			::= { hmWanMbusE2 68 }

hmWanMbusE2Value1F		OBJECT-TYPE
			SYNTAX	INTEGER
			MAX-ACCESS	read-only
			STATUS	current
			::= { hmWanMbusE2 69 }

hmWanMbusE2VIF20		OBJECT-TYPE
			SYNTAX	INTEGER
			MAX-ACCESS	read-only
			STATUS	current
			::= { hmWanMbusE2 70 }

hmWanMbusE2Value20		OBJECT-TYPE
			SYNTAX	INTEGER
			MAX-ACCESS	read-only
			STATUS	current
			::= { hmWanMbusE2 71 }

hmWanMbusE2VIF21		OBJECT-TYPE
			SYNTAX	INTEGER
			MAX-ACCESS	read-only
			STATUS	current
			::= { hmWanMbusE2 72 }

hmWanMbusE2Value21		OBJECT-TYPE
			SYNTAX	INTEGER
			MAX-ACCESS	read-only
			STATUS	current
			::= { hmWanMbusE2 73 }

hmWanMbusE2VIF22		OBJECT-TYPE
			SYNTAX	INTEGER
			MAX-ACCESS	read-only
			STATUS	current
			::= { hmWanMbusE2 74 }

hmWanMbusE2Value22		OBJECT-TYPE
			SYNTAX	INTEGER
			MAX-ACCESS	read-only
			STATUS	current
			::= { hmWanMbusE2 75 }

hmWanMbusE2VIF23		OBJECT-TYPE
			SYNTAX	INTEGER
			MAX-ACCESS	read-only
			STATUS	current
			::= { hmWanMbusE2 76 }

hmWanMbusE2Value23		OBJECT-TYPE
			SYNTAX	INTEGER
			MAX-ACCESS	read-only
			STATUS	current
			::= { hmWanMbusE2 77 }

hmWanMbusE2VIF24		OBJECT-TYPE
			SYNTAX	INTEGER
			MAX-ACCESS	read-only
			STATUS	current
			::= { hmWanMbusE2 78 }

hmWanMbusE2Value24		OBJECT-TYPE
			SYNTAX	INTEGER
			MAX-ACCESS	read-only
			STATUS	current
			::= { hmWanMbusE2 79 }

hmWanMbusE2VIF25		OBJECT-TYPE
			SYNTAX	INTEGER
			MAX-ACCESS	read-only
			STATUS	current
			::= { hmWanMbusE2 80 }

hmWanMbusE2Value25		OBJECT-TYPE
			SYNTAX	INTEGER
			MAX-ACCESS	read-only
			STATUS	current
			::= { hmWanMbusE2 81 }

hmWanMbusE2VIF26		OBJECT-TYPE
			SYNTAX	INTEGER
			MAX-ACCESS	read-only
			STATUS	current
			::= { hmWanMbusE2 82 }

hmWanMbusE2Value26		OBJECT-TYPE
			SYNTAX	INTEGER
			MAX-ACCESS	read-only
			STATUS	current
			::= { hmWanMbusE2 83 }

hmWanMbusE2VIF27		OBJECT-TYPE
			SYNTAX	INTEGER
			MAX-ACCESS	read-only
			STATUS	current
			::= { hmWanMbusE2 84 }

hmWanMbusE2Value27		OBJECT-TYPE
			SYNTAX	INTEGER
			MAX-ACCESS	read-only
			STATUS	current
			::= { hmWanMbusE2 85 }

hmWanMbusE2VIF28		OBJECT-TYPE
			SYNTAX	INTEGER
			MAX-ACCESS	read-only
			STATUS	current
			::= { hmWanMbusE2 86 }

hmWanMbusE2Value28		OBJECT-TYPE
			SYNTAX	INTEGER
			MAX-ACCESS	read-only
			STATUS	current
			::= { hmWanMbusE2 87 }

hmWanMbusE2VIF29		OBJECT-TYPE
			SYNTAX	INTEGER
			MAX-ACCESS	read-only
			STATUS	current
			::= { hmWanMbusE2 88 }

hmWanMbusE2Value29		OBJECT-TYPE
			SYNTAX	INTEGER
			MAX-ACCESS	read-only
			STATUS	current
			::= { hmWanMbusE2 89 }

hmWanMbusE2VIF2A		OBJECT-TYPE
			SYNTAX	INTEGER
			MAX-ACCESS	read-only
			STATUS	current
			::= { hmWanMbusE2 90 }

hmWanMbusE2Value2A		OBJECT-TYPE
			SYNTAX	INTEGER
			MAX-ACCESS	read-only
			STATUS	current
			::= { hmWanMbusE2 91 }

hmWanMbusE2VIF2B		OBJECT-TYPE
			SYNTAX	INTEGER
			MAX-ACCESS	read-only
			STATUS	current
			::= { hmWanMbusE2 92 }

hmWanMbusE2Value2B		OBJECT-TYPE
			SYNTAX	INTEGER
			MAX-ACCESS	read-only
			STATUS	current
			::= { hmWanMbusE2 93 }

hmWanMbusE2VIF2C		OBJECT-TYPE
			SYNTAX	INTEGER
			MAX-ACCESS	read-only
			STATUS	current
			::= { hmWanMbusE2 94 }

hmWanMbusE2Value2C		OBJECT-TYPE
			SYNTAX	INTEGER
			MAX-ACCESS	read-only
			STATUS	current
			::= { hmWanMbusE2 95 }

hmWanMbusE2VIF2D		OBJECT-TYPE
			SYNTAX	INTEGER
			MAX-ACCESS	read-only
			STATUS	current
			::= { hmWanMbusE2 96 }

hmWanMbusE2Value2D		OBJECT-TYPE
			SYNTAX	INTEGER
			MAX-ACCESS	read-only
			STATUS	current
			::= { hmWanMbusE2 97 }

hmWanMbusE2VIF2E		OBJECT-TYPE
			SYNTAX	INTEGER
			MAX-ACCESS	read-only
			STATUS	current
			::= { hmWanMbusE2 98 }

hmWanMbusE2Value2E		OBJECT-TYPE
			SYNTAX	INTEGER
			MAX-ACCESS	read-only
			STATUS	current
			::= { hmWanMbusE2 99 }

hmWanMbusE2VIF2F		OBJECT-TYPE
			SYNTAX	INTEGER
			MAX-ACCESS	read-only
			STATUS	current
			::= { hmWanMbusE2 100 }

hmWanMbusE2Value2F		OBJECT-TYPE
			SYNTAX	INTEGER
			MAX-ACCESS	read-only
			STATUS	current
			::= { hmWanMbusE2 101 }

hmWanMbusE3			OBJECT IDENTIFIER ::= { hmWanMbus 227 }

hmWanMbusE3IdNumber		OBJECT-TYPE
			SYNTAX	Gauge32
			MAX-ACCESS	read-only
			STATUS	current
			::= { hmWanMbusE3 1 }

hmWanMbusE3Manufacturer	OBJECT-TYPE
			SYNTAX	Gauge32
			MAX-ACCESS	read-only
			STATUS	current
			::= { hmWanMbusE3 2 }

hmWanMbusE3Version		OBJECT-TYPE
			SYNTAX	Gauge32
			MAX-ACCESS	read-only
			STATUS	current
			::= { hmWanMbusE3 3 }

hmWanMbusE3Medium		OBJECT-TYPE
			SYNTAX	Gauge32
			MAX-ACCESS	read-only
			STATUS	current
			::= { hmWanMbusE3 4 }

hmWanMbusE3Status		OBJECT-TYPE
			SYNTAX	Gauge32
			MAX-ACCESS	read-only
			STATUS	current
			::= { hmWanMbusE3 5 }

hmWanMbusE3VIF00		OBJECT-TYPE
			SYNTAX	INTEGER
			MAX-ACCESS	read-only
			STATUS	current
			::= { hmWanMbusE3 6 }

hmWanMbusE3Value00		OBJECT-TYPE
			SYNTAX	INTEGER
			MAX-ACCESS	read-only
			STATUS	current
			::= { hmWanMbusE3 7 }

hmWanMbusE3VIF01		OBJECT-TYPE
			SYNTAX	INTEGER
			MAX-ACCESS	read-only
			STATUS	current
			::= { hmWanMbusE3 8 }

hmWanMbusE3Value01		OBJECT-TYPE
			SYNTAX	INTEGER
			MAX-ACCESS	read-only
			STATUS	current
			::= { hmWanMbusE3 9 }

hmWanMbusE3VIF02		OBJECT-TYPE
			SYNTAX	INTEGER
			MAX-ACCESS	read-only
			STATUS	current
			::= { hmWanMbusE3 10 }

hmWanMbusE3Value02		OBJECT-TYPE
			SYNTAX	INTEGER
			MAX-ACCESS	read-only
			STATUS	current
			::= { hmWanMbusE3 11 }

hmWanMbusE3VIF03		OBJECT-TYPE
			SYNTAX	INTEGER
			MAX-ACCESS	read-only
			STATUS	current
			::= { hmWanMbusE3 12 }

hmWanMbusE3Value03		OBJECT-TYPE
			SYNTAX	INTEGER
			MAX-ACCESS	read-only
			STATUS	current
			::= { hmWanMbusE3 13 }

hmWanMbusE3VIF04		OBJECT-TYPE
			SYNTAX	INTEGER
			MAX-ACCESS	read-only
			STATUS	current
			::= { hmWanMbusE3 14 }

hmWanMbusE3Value04		OBJECT-TYPE
			SYNTAX	INTEGER
			MAX-ACCESS	read-only
			STATUS	current
			::= { hmWanMbusE3 15 }

hmWanMbusE3VIF05		OBJECT-TYPE
			SYNTAX	INTEGER
			MAX-ACCESS	read-only
			STATUS	current
			::= { hmWanMbusE3 16 }

hmWanMbusE3Value05		OBJECT-TYPE
			SYNTAX	INTEGER
			MAX-ACCESS	read-only
			STATUS	current
			::= { hmWanMbusE3 17 }

hmWanMbusE3VIF06		OBJECT-TYPE
			SYNTAX	INTEGER
			MAX-ACCESS	read-only
			STATUS	current
			::= { hmWanMbusE3 18 }

hmWanMbusE3Value06		OBJECT-TYPE
			SYNTAX	INTEGER
			MAX-ACCESS	read-only
			STATUS	current
			::= { hmWanMbusE3 19 }

hmWanMbusE3VIF07		OBJECT-TYPE
			SYNTAX	INTEGER
			MAX-ACCESS	read-only
			STATUS	current
			::= { hmWanMbusE3 20 }

hmWanMbusE3Value07		OBJECT-TYPE
			SYNTAX	INTEGER
			MAX-ACCESS	read-only
			STATUS	current
			::= { hmWanMbusE3 21 }

hmWanMbusE3VIF08		OBJECT-TYPE
			SYNTAX	INTEGER
			MAX-ACCESS	read-only
			STATUS	current
			::= { hmWanMbusE3 22 }

hmWanMbusE3Value08		OBJECT-TYPE
			SYNTAX	INTEGER
			MAX-ACCESS	read-only
			STATUS	current
			::= { hmWanMbusE3 23 }

hmWanMbusE3VIF09		OBJECT-TYPE
			SYNTAX	INTEGER
			MAX-ACCESS	read-only
			STATUS	current
			::= { hmWanMbusE3 24 }

hmWanMbusE3Value09		OBJECT-TYPE
			SYNTAX	INTEGER
			MAX-ACCESS	read-only
			STATUS	current
			::= { hmWanMbusE3 25 }

hmWanMbusE3VIF0A		OBJECT-TYPE
			SYNTAX	INTEGER
			MAX-ACCESS	read-only
			STATUS	current
			::= { hmWanMbusE3 26 }

hmWanMbusE3Value0A		OBJECT-TYPE
			SYNTAX	INTEGER
			MAX-ACCESS	read-only
			STATUS	current
			::= { hmWanMbusE3 27 }

hmWanMbusE3VIF0B		OBJECT-TYPE
			SYNTAX	INTEGER
			MAX-ACCESS	read-only
			STATUS	current
			::= { hmWanMbusE3 28 }

hmWanMbusE3Value0B		OBJECT-TYPE
			SYNTAX	INTEGER
			MAX-ACCESS	read-only
			STATUS	current
			::= { hmWanMbusE3 29 }

hmWanMbusE3VIF0C		OBJECT-TYPE
			SYNTAX	INTEGER
			MAX-ACCESS	read-only
			STATUS	current
			::= { hmWanMbusE3 30 }

hmWanMbusE3Value0C		OBJECT-TYPE
			SYNTAX	INTEGER
			MAX-ACCESS	read-only
			STATUS	current
			::= { hmWanMbusE3 31 }

hmWanMbusE3VIF0D		OBJECT-TYPE
			SYNTAX	INTEGER
			MAX-ACCESS	read-only
			STATUS	current
			::= { hmWanMbusE3 32 }

hmWanMbusE3Value0D		OBJECT-TYPE
			SYNTAX	INTEGER
			MAX-ACCESS	read-only
			STATUS	current
			::= { hmWanMbusE3 33 }

hmWanMbusE3VIF0E		OBJECT-TYPE
			SYNTAX	INTEGER
			MAX-ACCESS	read-only
			STATUS	current
			::= { hmWanMbusE3 34 }

hmWanMbusE3Value0E		OBJECT-TYPE
			SYNTAX	INTEGER
			MAX-ACCESS	read-only
			STATUS	current
			::= { hmWanMbusE3 35 }

hmWanMbusE3VIF0F		OBJECT-TYPE
			SYNTAX	INTEGER
			MAX-ACCESS	read-only
			STATUS	current
			::= { hmWanMbusE3 36 }

hmWanMbusE3Value0F		OBJECT-TYPE
			SYNTAX	INTEGER
			MAX-ACCESS	read-only
			STATUS	current
			::= { hmWanMbusE3 37 }

hmWanMbusE3VIF10		OBJECT-TYPE
			SYNTAX	INTEGER
			MAX-ACCESS	read-only
			STATUS	current
			::= { hmWanMbusE3 38 }

hmWanMbusE3Value10		OBJECT-TYPE
			SYNTAX	INTEGER
			MAX-ACCESS	read-only
			STATUS	current
			::= { hmWanMbusE3 39 }

hmWanMbusE3VIF11		OBJECT-TYPE
			SYNTAX	INTEGER
			MAX-ACCESS	read-only
			STATUS	current
			::= { hmWanMbusE3 40 }

hmWanMbusE3Value11		OBJECT-TYPE
			SYNTAX	INTEGER
			MAX-ACCESS	read-only
			STATUS	current
			::= { hmWanMbusE3 41 }

hmWanMbusE3VIF12		OBJECT-TYPE
			SYNTAX	INTEGER
			MAX-ACCESS	read-only
			STATUS	current
			::= { hmWanMbusE3 42 }

hmWanMbusE3Value12		OBJECT-TYPE
			SYNTAX	INTEGER
			MAX-ACCESS	read-only
			STATUS	current
			::= { hmWanMbusE3 43 }

hmWanMbusE3VIF13		OBJECT-TYPE
			SYNTAX	INTEGER
			MAX-ACCESS	read-only
			STATUS	current
			::= { hmWanMbusE3 44 }

hmWanMbusE3Value13		OBJECT-TYPE
			SYNTAX	INTEGER
			MAX-ACCESS	read-only
			STATUS	current
			::= { hmWanMbusE3 45 }

hmWanMbusE3VIF14		OBJECT-TYPE
			SYNTAX	INTEGER
			MAX-ACCESS	read-only
			STATUS	current
			::= { hmWanMbusE3 46 }

hmWanMbusE3Value14		OBJECT-TYPE
			SYNTAX	INTEGER
			MAX-ACCESS	read-only
			STATUS	current
			::= { hmWanMbusE3 47 }

hmWanMbusE3VIF15		OBJECT-TYPE
			SYNTAX	INTEGER
			MAX-ACCESS	read-only
			STATUS	current
			::= { hmWanMbusE3 48 }

hmWanMbusE3Value15		OBJECT-TYPE
			SYNTAX	INTEGER
			MAX-ACCESS	read-only
			STATUS	current
			::= { hmWanMbusE3 49 }

hmWanMbusE3VIF16		OBJECT-TYPE
			SYNTAX	INTEGER
			MAX-ACCESS	read-only
			STATUS	current
			::= { hmWanMbusE3 50 }

hmWanMbusE3Value16		OBJECT-TYPE
			SYNTAX	INTEGER
			MAX-ACCESS	read-only
			STATUS	current
			::= { hmWanMbusE3 51 }

hmWanMbusE3VIF17		OBJECT-TYPE
			SYNTAX	INTEGER
			MAX-ACCESS	read-only
			STATUS	current
			::= { hmWanMbusE3 52 }

hmWanMbusE3Value17		OBJECT-TYPE
			SYNTAX	INTEGER
			MAX-ACCESS	read-only
			STATUS	current
			::= { hmWanMbusE3 53 }

hmWanMbusE3VIF18		OBJECT-TYPE
			SYNTAX	INTEGER
			MAX-ACCESS	read-only
			STATUS	current
			::= { hmWanMbusE3 54 }

hmWanMbusE3Value18		OBJECT-TYPE
			SYNTAX	INTEGER
			MAX-ACCESS	read-only
			STATUS	current
			::= { hmWanMbusE3 55 }

hmWanMbusE3VIF19		OBJECT-TYPE
			SYNTAX	INTEGER
			MAX-ACCESS	read-only
			STATUS	current
			::= { hmWanMbusE3 56 }

hmWanMbusE3Value19		OBJECT-TYPE
			SYNTAX	INTEGER
			MAX-ACCESS	read-only
			STATUS	current
			::= { hmWanMbusE3 57 }

hmWanMbusE3VIF1A		OBJECT-TYPE
			SYNTAX	INTEGER
			MAX-ACCESS	read-only
			STATUS	current
			::= { hmWanMbusE3 58 }

hmWanMbusE3Value1A		OBJECT-TYPE
			SYNTAX	INTEGER
			MAX-ACCESS	read-only
			STATUS	current
			::= { hmWanMbusE3 59 }

hmWanMbusE3VIF1B		OBJECT-TYPE
			SYNTAX	INTEGER
			MAX-ACCESS	read-only
			STATUS	current
			::= { hmWanMbusE3 60 }

hmWanMbusE3Value1B		OBJECT-TYPE
			SYNTAX	INTEGER
			MAX-ACCESS	read-only
			STATUS	current
			::= { hmWanMbusE3 61 }

hmWanMbusE3VIF1C		OBJECT-TYPE
			SYNTAX	INTEGER
			MAX-ACCESS	read-only
			STATUS	current
			::= { hmWanMbusE3 62 }

hmWanMbusE3Value1C		OBJECT-TYPE
			SYNTAX	INTEGER
			MAX-ACCESS	read-only
			STATUS	current
			::= { hmWanMbusE3 63 }

hmWanMbusE3VIF1D		OBJECT-TYPE
			SYNTAX	INTEGER
			MAX-ACCESS	read-only
			STATUS	current
			::= { hmWanMbusE3 64 }

hmWanMbusE3Value1D		OBJECT-TYPE
			SYNTAX	INTEGER
			MAX-ACCESS	read-only
			STATUS	current
			::= { hmWanMbusE3 65 }

hmWanMbusE3VIF1E		OBJECT-TYPE
			SYNTAX	INTEGER
			MAX-ACCESS	read-only
			STATUS	current
			::= { hmWanMbusE3 66 }

hmWanMbusE3Value1E		OBJECT-TYPE
			SYNTAX	INTEGER
			MAX-ACCESS	read-only
			STATUS	current
			::= { hmWanMbusE3 67 }

hmWanMbusE3VIF1F		OBJECT-TYPE
			SYNTAX	INTEGER
			MAX-ACCESS	read-only
			STATUS	current
			::= { hmWanMbusE3 68 }

hmWanMbusE3Value1F		OBJECT-TYPE
			SYNTAX	INTEGER
			MAX-ACCESS	read-only
			STATUS	current
			::= { hmWanMbusE3 69 }

hmWanMbusE3VIF20		OBJECT-TYPE
			SYNTAX	INTEGER
			MAX-ACCESS	read-only
			STATUS	current
			::= { hmWanMbusE3 70 }

hmWanMbusE3Value20		OBJECT-TYPE
			SYNTAX	INTEGER
			MAX-ACCESS	read-only
			STATUS	current
			::= { hmWanMbusE3 71 }

hmWanMbusE3VIF21		OBJECT-TYPE
			SYNTAX	INTEGER
			MAX-ACCESS	read-only
			STATUS	current
			::= { hmWanMbusE3 72 }

hmWanMbusE3Value21		OBJECT-TYPE
			SYNTAX	INTEGER
			MAX-ACCESS	read-only
			STATUS	current
			::= { hmWanMbusE3 73 }

hmWanMbusE3VIF22		OBJECT-TYPE
			SYNTAX	INTEGER
			MAX-ACCESS	read-only
			STATUS	current
			::= { hmWanMbusE3 74 }

hmWanMbusE3Value22		OBJECT-TYPE
			SYNTAX	INTEGER
			MAX-ACCESS	read-only
			STATUS	current
			::= { hmWanMbusE3 75 }

hmWanMbusE3VIF23		OBJECT-TYPE
			SYNTAX	INTEGER
			MAX-ACCESS	read-only
			STATUS	current
			::= { hmWanMbusE3 76 }

hmWanMbusE3Value23		OBJECT-TYPE
			SYNTAX	INTEGER
			MAX-ACCESS	read-only
			STATUS	current
			::= { hmWanMbusE3 77 }

hmWanMbusE3VIF24		OBJECT-TYPE
			SYNTAX	INTEGER
			MAX-ACCESS	read-only
			STATUS	current
			::= { hmWanMbusE3 78 }

hmWanMbusE3Value24		OBJECT-TYPE
			SYNTAX	INTEGER
			MAX-ACCESS	read-only
			STATUS	current
			::= { hmWanMbusE3 79 }

hmWanMbusE3VIF25		OBJECT-TYPE
			SYNTAX	INTEGER
			MAX-ACCESS	read-only
			STATUS	current
			::= { hmWanMbusE3 80 }

hmWanMbusE3Value25		OBJECT-TYPE
			SYNTAX	INTEGER
			MAX-ACCESS	read-only
			STATUS	current
			::= { hmWanMbusE3 81 }

hmWanMbusE3VIF26		OBJECT-TYPE
			SYNTAX	INTEGER
			MAX-ACCESS	read-only
			STATUS	current
			::= { hmWanMbusE3 82 }

hmWanMbusE3Value26		OBJECT-TYPE
			SYNTAX	INTEGER
			MAX-ACCESS	read-only
			STATUS	current
			::= { hmWanMbusE3 83 }

hmWanMbusE3VIF27		OBJECT-TYPE
			SYNTAX	INTEGER
			MAX-ACCESS	read-only
			STATUS	current
			::= { hmWanMbusE3 84 }

hmWanMbusE3Value27		OBJECT-TYPE
			SYNTAX	INTEGER
			MAX-ACCESS	read-only
			STATUS	current
			::= { hmWanMbusE3 85 }

hmWanMbusE3VIF28		OBJECT-TYPE
			SYNTAX	INTEGER
			MAX-ACCESS	read-only
			STATUS	current
			::= { hmWanMbusE3 86 }

hmWanMbusE3Value28		OBJECT-TYPE
			SYNTAX	INTEGER
			MAX-ACCESS	read-only
			STATUS	current
			::= { hmWanMbusE3 87 }

hmWanMbusE3VIF29		OBJECT-TYPE
			SYNTAX	INTEGER
			MAX-ACCESS	read-only
			STATUS	current
			::= { hmWanMbusE3 88 }

hmWanMbusE3Value29		OBJECT-TYPE
			SYNTAX	INTEGER
			MAX-ACCESS	read-only
			STATUS	current
			::= { hmWanMbusE3 89 }

hmWanMbusE3VIF2A		OBJECT-TYPE
			SYNTAX	INTEGER
			MAX-ACCESS	read-only
			STATUS	current
			::= { hmWanMbusE3 90 }

hmWanMbusE3Value2A		OBJECT-TYPE
			SYNTAX	INTEGER
			MAX-ACCESS	read-only
			STATUS	current
			::= { hmWanMbusE3 91 }

hmWanMbusE3VIF2B		OBJECT-TYPE
			SYNTAX	INTEGER
			MAX-ACCESS	read-only
			STATUS	current
			::= { hmWanMbusE3 92 }

hmWanMbusE3Value2B		OBJECT-TYPE
			SYNTAX	INTEGER
			MAX-ACCESS	read-only
			STATUS	current
			::= { hmWanMbusE3 93 }

hmWanMbusE3VIF2C		OBJECT-TYPE
			SYNTAX	INTEGER
			MAX-ACCESS	read-only
			STATUS	current
			::= { hmWanMbusE3 94 }

hmWanMbusE3Value2C		OBJECT-TYPE
			SYNTAX	INTEGER
			MAX-ACCESS	read-only
			STATUS	current
			::= { hmWanMbusE3 95 }

hmWanMbusE3VIF2D		OBJECT-TYPE
			SYNTAX	INTEGER
			MAX-ACCESS	read-only
			STATUS	current
			::= { hmWanMbusE3 96 }

hmWanMbusE3Value2D		OBJECT-TYPE
			SYNTAX	INTEGER
			MAX-ACCESS	read-only
			STATUS	current
			::= { hmWanMbusE3 97 }

hmWanMbusE3VIF2E		OBJECT-TYPE
			SYNTAX	INTEGER
			MAX-ACCESS	read-only
			STATUS	current
			::= { hmWanMbusE3 98 }

hmWanMbusE3Value2E		OBJECT-TYPE
			SYNTAX	INTEGER
			MAX-ACCESS	read-only
			STATUS	current
			::= { hmWanMbusE3 99 }

hmWanMbusE3VIF2F		OBJECT-TYPE
			SYNTAX	INTEGER
			MAX-ACCESS	read-only
			STATUS	current
			::= { hmWanMbusE3 100 }

hmWanMbusE3Value2F		OBJECT-TYPE
			SYNTAX	INTEGER
			MAX-ACCESS	read-only
			STATUS	current
			::= { hmWanMbusE3 101 }

hmWanMbusE4			OBJECT IDENTIFIER ::= { hmWanMbus 228 }

hmWanMbusE4IdNumber		OBJECT-TYPE
			SYNTAX	Gauge32
			MAX-ACCESS	read-only
			STATUS	current
			::= { hmWanMbusE4 1 }

hmWanMbusE4Manufacturer	OBJECT-TYPE
			SYNTAX	Gauge32
			MAX-ACCESS	read-only
			STATUS	current
			::= { hmWanMbusE4 2 }

hmWanMbusE4Version		OBJECT-TYPE
			SYNTAX	Gauge32
			MAX-ACCESS	read-only
			STATUS	current
			::= { hmWanMbusE4 3 }

hmWanMbusE4Medium		OBJECT-TYPE
			SYNTAX	Gauge32
			MAX-ACCESS	read-only
			STATUS	current
			::= { hmWanMbusE4 4 }

hmWanMbusE4Status		OBJECT-TYPE
			SYNTAX	Gauge32
			MAX-ACCESS	read-only
			STATUS	current
			::= { hmWanMbusE4 5 }

hmWanMbusE4VIF00		OBJECT-TYPE
			SYNTAX	INTEGER
			MAX-ACCESS	read-only
			STATUS	current
			::= { hmWanMbusE4 6 }

hmWanMbusE4Value00		OBJECT-TYPE
			SYNTAX	INTEGER
			MAX-ACCESS	read-only
			STATUS	current
			::= { hmWanMbusE4 7 }

hmWanMbusE4VIF01		OBJECT-TYPE
			SYNTAX	INTEGER
			MAX-ACCESS	read-only
			STATUS	current
			::= { hmWanMbusE4 8 }

hmWanMbusE4Value01		OBJECT-TYPE
			SYNTAX	INTEGER
			MAX-ACCESS	read-only
			STATUS	current
			::= { hmWanMbusE4 9 }

hmWanMbusE4VIF02		OBJECT-TYPE
			SYNTAX	INTEGER
			MAX-ACCESS	read-only
			STATUS	current
			::= { hmWanMbusE4 10 }

hmWanMbusE4Value02		OBJECT-TYPE
			SYNTAX	INTEGER
			MAX-ACCESS	read-only
			STATUS	current
			::= { hmWanMbusE4 11 }

hmWanMbusE4VIF03		OBJECT-TYPE
			SYNTAX	INTEGER
			MAX-ACCESS	read-only
			STATUS	current
			::= { hmWanMbusE4 12 }

hmWanMbusE4Value03		OBJECT-TYPE
			SYNTAX	INTEGER
			MAX-ACCESS	read-only
			STATUS	current
			::= { hmWanMbusE4 13 }

hmWanMbusE4VIF04		OBJECT-TYPE
			SYNTAX	INTEGER
			MAX-ACCESS	read-only
			STATUS	current
			::= { hmWanMbusE4 14 }

hmWanMbusE4Value04		OBJECT-TYPE
			SYNTAX	INTEGER
			MAX-ACCESS	read-only
			STATUS	current
			::= { hmWanMbusE4 15 }

hmWanMbusE4VIF05		OBJECT-TYPE
			SYNTAX	INTEGER
			MAX-ACCESS	read-only
			STATUS	current
			::= { hmWanMbusE4 16 }

hmWanMbusE4Value05		OBJECT-TYPE
			SYNTAX	INTEGER
			MAX-ACCESS	read-only
			STATUS	current
			::= { hmWanMbusE4 17 }

hmWanMbusE4VIF06		OBJECT-TYPE
			SYNTAX	INTEGER
			MAX-ACCESS	read-only
			STATUS	current
			::= { hmWanMbusE4 18 }

hmWanMbusE4Value06		OBJECT-TYPE
			SYNTAX	INTEGER
			MAX-ACCESS	read-only
			STATUS	current
			::= { hmWanMbusE4 19 }

hmWanMbusE4VIF07		OBJECT-TYPE
			SYNTAX	INTEGER
			MAX-ACCESS	read-only
			STATUS	current
			::= { hmWanMbusE4 20 }

hmWanMbusE4Value07		OBJECT-TYPE
			SYNTAX	INTEGER
			MAX-ACCESS	read-only
			STATUS	current
			::= { hmWanMbusE4 21 }

hmWanMbusE4VIF08		OBJECT-TYPE
			SYNTAX	INTEGER
			MAX-ACCESS	read-only
			STATUS	current
			::= { hmWanMbusE4 22 }

hmWanMbusE4Value08		OBJECT-TYPE
			SYNTAX	INTEGER
			MAX-ACCESS	read-only
			STATUS	current
			::= { hmWanMbusE4 23 }

hmWanMbusE4VIF09		OBJECT-TYPE
			SYNTAX	INTEGER
			MAX-ACCESS	read-only
			STATUS	current
			::= { hmWanMbusE4 24 }

hmWanMbusE4Value09		OBJECT-TYPE
			SYNTAX	INTEGER
			MAX-ACCESS	read-only
			STATUS	current
			::= { hmWanMbusE4 25 }

hmWanMbusE4VIF0A		OBJECT-TYPE
			SYNTAX	INTEGER
			MAX-ACCESS	read-only
			STATUS	current
			::= { hmWanMbusE4 26 }

hmWanMbusE4Value0A		OBJECT-TYPE
			SYNTAX	INTEGER
			MAX-ACCESS	read-only
			STATUS	current
			::= { hmWanMbusE4 27 }

hmWanMbusE4VIF0B		OBJECT-TYPE
			SYNTAX	INTEGER
			MAX-ACCESS	read-only
			STATUS	current
			::= { hmWanMbusE4 28 }

hmWanMbusE4Value0B		OBJECT-TYPE
			SYNTAX	INTEGER
			MAX-ACCESS	read-only
			STATUS	current
			::= { hmWanMbusE4 29 }

hmWanMbusE4VIF0C		OBJECT-TYPE
			SYNTAX	INTEGER
			MAX-ACCESS	read-only
			STATUS	current
			::= { hmWanMbusE4 30 }

hmWanMbusE4Value0C		OBJECT-TYPE
			SYNTAX	INTEGER
			MAX-ACCESS	read-only
			STATUS	current
			::= { hmWanMbusE4 31 }

hmWanMbusE4VIF0D		OBJECT-TYPE
			SYNTAX	INTEGER
			MAX-ACCESS	read-only
			STATUS	current
			::= { hmWanMbusE4 32 }

hmWanMbusE4Value0D		OBJECT-TYPE
			SYNTAX	INTEGER
			MAX-ACCESS	read-only
			STATUS	current
			::= { hmWanMbusE4 33 }

hmWanMbusE4VIF0E		OBJECT-TYPE
			SYNTAX	INTEGER
			MAX-ACCESS	read-only
			STATUS	current
			::= { hmWanMbusE4 34 }

hmWanMbusE4Value0E		OBJECT-TYPE
			SYNTAX	INTEGER
			MAX-ACCESS	read-only
			STATUS	current
			::= { hmWanMbusE4 35 }

hmWanMbusE4VIF0F		OBJECT-TYPE
			SYNTAX	INTEGER
			MAX-ACCESS	read-only
			STATUS	current
			::= { hmWanMbusE4 36 }

hmWanMbusE4Value0F		OBJECT-TYPE
			SYNTAX	INTEGER
			MAX-ACCESS	read-only
			STATUS	current
			::= { hmWanMbusE4 37 }

hmWanMbusE4VIF10		OBJECT-TYPE
			SYNTAX	INTEGER
			MAX-ACCESS	read-only
			STATUS	current
			::= { hmWanMbusE4 38 }

hmWanMbusE4Value10		OBJECT-TYPE
			SYNTAX	INTEGER
			MAX-ACCESS	read-only
			STATUS	current
			::= { hmWanMbusE4 39 }

hmWanMbusE4VIF11		OBJECT-TYPE
			SYNTAX	INTEGER
			MAX-ACCESS	read-only
			STATUS	current
			::= { hmWanMbusE4 40 }

hmWanMbusE4Value11		OBJECT-TYPE
			SYNTAX	INTEGER
			MAX-ACCESS	read-only
			STATUS	current
			::= { hmWanMbusE4 41 }

hmWanMbusE4VIF12		OBJECT-TYPE
			SYNTAX	INTEGER
			MAX-ACCESS	read-only
			STATUS	current
			::= { hmWanMbusE4 42 }

hmWanMbusE4Value12		OBJECT-TYPE
			SYNTAX	INTEGER
			MAX-ACCESS	read-only
			STATUS	current
			::= { hmWanMbusE4 43 }

hmWanMbusE4VIF13		OBJECT-TYPE
			SYNTAX	INTEGER
			MAX-ACCESS	read-only
			STATUS	current
			::= { hmWanMbusE4 44 }

hmWanMbusE4Value13		OBJECT-TYPE
			SYNTAX	INTEGER
			MAX-ACCESS	read-only
			STATUS	current
			::= { hmWanMbusE4 45 }

hmWanMbusE4VIF14		OBJECT-TYPE
			SYNTAX	INTEGER
			MAX-ACCESS	read-only
			STATUS	current
			::= { hmWanMbusE4 46 }

hmWanMbusE4Value14		OBJECT-TYPE
			SYNTAX	INTEGER
			MAX-ACCESS	read-only
			STATUS	current
			::= { hmWanMbusE4 47 }

hmWanMbusE4VIF15		OBJECT-TYPE
			SYNTAX	INTEGER
			MAX-ACCESS	read-only
			STATUS	current
			::= { hmWanMbusE4 48 }

hmWanMbusE4Value15		OBJECT-TYPE
			SYNTAX	INTEGER
			MAX-ACCESS	read-only
			STATUS	current
			::= { hmWanMbusE4 49 }

hmWanMbusE4VIF16		OBJECT-TYPE
			SYNTAX	INTEGER
			MAX-ACCESS	read-only
			STATUS	current
			::= { hmWanMbusE4 50 }

hmWanMbusE4Value16		OBJECT-TYPE
			SYNTAX	INTEGER
			MAX-ACCESS	read-only
			STATUS	current
			::= { hmWanMbusE4 51 }

hmWanMbusE4VIF17		OBJECT-TYPE
			SYNTAX	INTEGER
			MAX-ACCESS	read-only
			STATUS	current
			::= { hmWanMbusE4 52 }

hmWanMbusE4Value17		OBJECT-TYPE
			SYNTAX	INTEGER
			MAX-ACCESS	read-only
			STATUS	current
			::= { hmWanMbusE4 53 }

hmWanMbusE4VIF18		OBJECT-TYPE
			SYNTAX	INTEGER
			MAX-ACCESS	read-only
			STATUS	current
			::= { hmWanMbusE4 54 }

hmWanMbusE4Value18		OBJECT-TYPE
			SYNTAX	INTEGER
			MAX-ACCESS	read-only
			STATUS	current
			::= { hmWanMbusE4 55 }

hmWanMbusE4VIF19		OBJECT-TYPE
			SYNTAX	INTEGER
			MAX-ACCESS	read-only
			STATUS	current
			::= { hmWanMbusE4 56 }

hmWanMbusE4Value19		OBJECT-TYPE
			SYNTAX	INTEGER
			MAX-ACCESS	read-only
			STATUS	current
			::= { hmWanMbusE4 57 }

hmWanMbusE4VIF1A		OBJECT-TYPE
			SYNTAX	INTEGER
			MAX-ACCESS	read-only
			STATUS	current
			::= { hmWanMbusE4 58 }

hmWanMbusE4Value1A		OBJECT-TYPE
			SYNTAX	INTEGER
			MAX-ACCESS	read-only
			STATUS	current
			::= { hmWanMbusE4 59 }

hmWanMbusE4VIF1B		OBJECT-TYPE
			SYNTAX	INTEGER
			MAX-ACCESS	read-only
			STATUS	current
			::= { hmWanMbusE4 60 }

hmWanMbusE4Value1B		OBJECT-TYPE
			SYNTAX	INTEGER
			MAX-ACCESS	read-only
			STATUS	current
			::= { hmWanMbusE4 61 }

hmWanMbusE4VIF1C		OBJECT-TYPE
			SYNTAX	INTEGER
			MAX-ACCESS	read-only
			STATUS	current
			::= { hmWanMbusE4 62 }

hmWanMbusE4Value1C		OBJECT-TYPE
			SYNTAX	INTEGER
			MAX-ACCESS	read-only
			STATUS	current
			::= { hmWanMbusE4 63 }

hmWanMbusE4VIF1D		OBJECT-TYPE
			SYNTAX	INTEGER
			MAX-ACCESS	read-only
			STATUS	current
			::= { hmWanMbusE4 64 }

hmWanMbusE4Value1D		OBJECT-TYPE
			SYNTAX	INTEGER
			MAX-ACCESS	read-only
			STATUS	current
			::= { hmWanMbusE4 65 }

hmWanMbusE4VIF1E		OBJECT-TYPE
			SYNTAX	INTEGER
			MAX-ACCESS	read-only
			STATUS	current
			::= { hmWanMbusE4 66 }

hmWanMbusE4Value1E		OBJECT-TYPE
			SYNTAX	INTEGER
			MAX-ACCESS	read-only
			STATUS	current
			::= { hmWanMbusE4 67 }

hmWanMbusE4VIF1F		OBJECT-TYPE
			SYNTAX	INTEGER
			MAX-ACCESS	read-only
			STATUS	current
			::= { hmWanMbusE4 68 }

hmWanMbusE4Value1F		OBJECT-TYPE
			SYNTAX	INTEGER
			MAX-ACCESS	read-only
			STATUS	current
			::= { hmWanMbusE4 69 }

hmWanMbusE4VIF20		OBJECT-TYPE
			SYNTAX	INTEGER
			MAX-ACCESS	read-only
			STATUS	current
			::= { hmWanMbusE4 70 }

hmWanMbusE4Value20		OBJECT-TYPE
			SYNTAX	INTEGER
			MAX-ACCESS	read-only
			STATUS	current
			::= { hmWanMbusE4 71 }

hmWanMbusE4VIF21		OBJECT-TYPE
			SYNTAX	INTEGER
			MAX-ACCESS	read-only
			STATUS	current
			::= { hmWanMbusE4 72 }

hmWanMbusE4Value21		OBJECT-TYPE
			SYNTAX	INTEGER
			MAX-ACCESS	read-only
			STATUS	current
			::= { hmWanMbusE4 73 }

hmWanMbusE4VIF22		OBJECT-TYPE
			SYNTAX	INTEGER
			MAX-ACCESS	read-only
			STATUS	current
			::= { hmWanMbusE4 74 }

hmWanMbusE4Value22		OBJECT-TYPE
			SYNTAX	INTEGER
			MAX-ACCESS	read-only
			STATUS	current
			::= { hmWanMbusE4 75 }

hmWanMbusE4VIF23		OBJECT-TYPE
			SYNTAX	INTEGER
			MAX-ACCESS	read-only
			STATUS	current
			::= { hmWanMbusE4 76 }

hmWanMbusE4Value23		OBJECT-TYPE
			SYNTAX	INTEGER
			MAX-ACCESS	read-only
			STATUS	current
			::= { hmWanMbusE4 77 }

hmWanMbusE4VIF24		OBJECT-TYPE
			SYNTAX	INTEGER
			MAX-ACCESS	read-only
			STATUS	current
			::= { hmWanMbusE4 78 }

hmWanMbusE4Value24		OBJECT-TYPE
			SYNTAX	INTEGER
			MAX-ACCESS	read-only
			STATUS	current
			::= { hmWanMbusE4 79 }

hmWanMbusE4VIF25		OBJECT-TYPE
			SYNTAX	INTEGER
			MAX-ACCESS	read-only
			STATUS	current
			::= { hmWanMbusE4 80 }

hmWanMbusE4Value25		OBJECT-TYPE
			SYNTAX	INTEGER
			MAX-ACCESS	read-only
			STATUS	current
			::= { hmWanMbusE4 81 }

hmWanMbusE4VIF26		OBJECT-TYPE
			SYNTAX	INTEGER
			MAX-ACCESS	read-only
			STATUS	current
			::= { hmWanMbusE4 82 }

hmWanMbusE4Value26		OBJECT-TYPE
			SYNTAX	INTEGER
			MAX-ACCESS	read-only
			STATUS	current
			::= { hmWanMbusE4 83 }

hmWanMbusE4VIF27		OBJECT-TYPE
			SYNTAX	INTEGER
			MAX-ACCESS	read-only
			STATUS	current
			::= { hmWanMbusE4 84 }

hmWanMbusE4Value27		OBJECT-TYPE
			SYNTAX	INTEGER
			MAX-ACCESS	read-only
			STATUS	current
			::= { hmWanMbusE4 85 }

hmWanMbusE4VIF28		OBJECT-TYPE
			SYNTAX	INTEGER
			MAX-ACCESS	read-only
			STATUS	current
			::= { hmWanMbusE4 86 }

hmWanMbusE4Value28		OBJECT-TYPE
			SYNTAX	INTEGER
			MAX-ACCESS	read-only
			STATUS	current
			::= { hmWanMbusE4 87 }

hmWanMbusE4VIF29		OBJECT-TYPE
			SYNTAX	INTEGER
			MAX-ACCESS	read-only
			STATUS	current
			::= { hmWanMbusE4 88 }

hmWanMbusE4Value29		OBJECT-TYPE
			SYNTAX	INTEGER
			MAX-ACCESS	read-only
			STATUS	current
			::= { hmWanMbusE4 89 }

hmWanMbusE4VIF2A		OBJECT-TYPE
			SYNTAX	INTEGER
			MAX-ACCESS	read-only
			STATUS	current
			::= { hmWanMbusE4 90 }

hmWanMbusE4Value2A		OBJECT-TYPE
			SYNTAX	INTEGER
			MAX-ACCESS	read-only
			STATUS	current
			::= { hmWanMbusE4 91 }

hmWanMbusE4VIF2B		OBJECT-TYPE
			SYNTAX	INTEGER
			MAX-ACCESS	read-only
			STATUS	current
			::= { hmWanMbusE4 92 }

hmWanMbusE4Value2B		OBJECT-TYPE
			SYNTAX	INTEGER
			MAX-ACCESS	read-only
			STATUS	current
			::= { hmWanMbusE4 93 }

hmWanMbusE4VIF2C		OBJECT-TYPE
			SYNTAX	INTEGER
			MAX-ACCESS	read-only
			STATUS	current
			::= { hmWanMbusE4 94 }

hmWanMbusE4Value2C		OBJECT-TYPE
			SYNTAX	INTEGER
			MAX-ACCESS	read-only
			STATUS	current
			::= { hmWanMbusE4 95 }

hmWanMbusE4VIF2D		OBJECT-TYPE
			SYNTAX	INTEGER
			MAX-ACCESS	read-only
			STATUS	current
			::= { hmWanMbusE4 96 }

hmWanMbusE4Value2D		OBJECT-TYPE
			SYNTAX	INTEGER
			MAX-ACCESS	read-only
			STATUS	current
			::= { hmWanMbusE4 97 }

hmWanMbusE4VIF2E		OBJECT-TYPE
			SYNTAX	INTEGER
			MAX-ACCESS	read-only
			STATUS	current
			::= { hmWanMbusE4 98 }

hmWanMbusE4Value2E		OBJECT-TYPE
			SYNTAX	INTEGER
			MAX-ACCESS	read-only
			STATUS	current
			::= { hmWanMbusE4 99 }

hmWanMbusE4VIF2F		OBJECT-TYPE
			SYNTAX	INTEGER
			MAX-ACCESS	read-only
			STATUS	current
			::= { hmWanMbusE4 100 }

hmWanMbusE4Value2F		OBJECT-TYPE
			SYNTAX	INTEGER
			MAX-ACCESS	read-only
			STATUS	current
			::= { hmWanMbusE4 101 }

hmWanMbusE5			OBJECT IDENTIFIER ::= { hmWanMbus 229 }

hmWanMbusE5IdNumber		OBJECT-TYPE
			SYNTAX	Gauge32
			MAX-ACCESS	read-only
			STATUS	current
			::= { hmWanMbusE5 1 }

hmWanMbusE5Manufacturer	OBJECT-TYPE
			SYNTAX	Gauge32
			MAX-ACCESS	read-only
			STATUS	current
			::= { hmWanMbusE5 2 }

hmWanMbusE5Version		OBJECT-TYPE
			SYNTAX	Gauge32
			MAX-ACCESS	read-only
			STATUS	current
			::= { hmWanMbusE5 3 }

hmWanMbusE5Medium		OBJECT-TYPE
			SYNTAX	Gauge32
			MAX-ACCESS	read-only
			STATUS	current
			::= { hmWanMbusE5 4 }

hmWanMbusE5Status		OBJECT-TYPE
			SYNTAX	Gauge32
			MAX-ACCESS	read-only
			STATUS	current
			::= { hmWanMbusE5 5 }

hmWanMbusE5VIF00		OBJECT-TYPE
			SYNTAX	INTEGER
			MAX-ACCESS	read-only
			STATUS	current
			::= { hmWanMbusE5 6 }

hmWanMbusE5Value00		OBJECT-TYPE
			SYNTAX	INTEGER
			MAX-ACCESS	read-only
			STATUS	current
			::= { hmWanMbusE5 7 }

hmWanMbusE5VIF01		OBJECT-TYPE
			SYNTAX	INTEGER
			MAX-ACCESS	read-only
			STATUS	current
			::= { hmWanMbusE5 8 }

hmWanMbusE5Value01		OBJECT-TYPE
			SYNTAX	INTEGER
			MAX-ACCESS	read-only
			STATUS	current
			::= { hmWanMbusE5 9 }

hmWanMbusE5VIF02		OBJECT-TYPE
			SYNTAX	INTEGER
			MAX-ACCESS	read-only
			STATUS	current
			::= { hmWanMbusE5 10 }

hmWanMbusE5Value02		OBJECT-TYPE
			SYNTAX	INTEGER
			MAX-ACCESS	read-only
			STATUS	current
			::= { hmWanMbusE5 11 }

hmWanMbusE5VIF03		OBJECT-TYPE
			SYNTAX	INTEGER
			MAX-ACCESS	read-only
			STATUS	current
			::= { hmWanMbusE5 12 }

hmWanMbusE5Value03		OBJECT-TYPE
			SYNTAX	INTEGER
			MAX-ACCESS	read-only
			STATUS	current
			::= { hmWanMbusE5 13 }

hmWanMbusE5VIF04		OBJECT-TYPE
			SYNTAX	INTEGER
			MAX-ACCESS	read-only
			STATUS	current
			::= { hmWanMbusE5 14 }

hmWanMbusE5Value04		OBJECT-TYPE
			SYNTAX	INTEGER
			MAX-ACCESS	read-only
			STATUS	current
			::= { hmWanMbusE5 15 }

hmWanMbusE5VIF05		OBJECT-TYPE
			SYNTAX	INTEGER
			MAX-ACCESS	read-only
			STATUS	current
			::= { hmWanMbusE5 16 }

hmWanMbusE5Value05		OBJECT-TYPE
			SYNTAX	INTEGER
			MAX-ACCESS	read-only
			STATUS	current
			::= { hmWanMbusE5 17 }

hmWanMbusE5VIF06		OBJECT-TYPE
			SYNTAX	INTEGER
			MAX-ACCESS	read-only
			STATUS	current
			::= { hmWanMbusE5 18 }

hmWanMbusE5Value06		OBJECT-TYPE
			SYNTAX	INTEGER
			MAX-ACCESS	read-only
			STATUS	current
			::= { hmWanMbusE5 19 }

hmWanMbusE5VIF07		OBJECT-TYPE
			SYNTAX	INTEGER
			MAX-ACCESS	read-only
			STATUS	current
			::= { hmWanMbusE5 20 }

hmWanMbusE5Value07		OBJECT-TYPE
			SYNTAX	INTEGER
			MAX-ACCESS	read-only
			STATUS	current
			::= { hmWanMbusE5 21 }

hmWanMbusE5VIF08		OBJECT-TYPE
			SYNTAX	INTEGER
			MAX-ACCESS	read-only
			STATUS	current
			::= { hmWanMbusE5 22 }

hmWanMbusE5Value08		OBJECT-TYPE
			SYNTAX	INTEGER
			MAX-ACCESS	read-only
			STATUS	current
			::= { hmWanMbusE5 23 }

hmWanMbusE5VIF09		OBJECT-TYPE
			SYNTAX	INTEGER
			MAX-ACCESS	read-only
			STATUS	current
			::= { hmWanMbusE5 24 }

hmWanMbusE5Value09		OBJECT-TYPE
			SYNTAX	INTEGER
			MAX-ACCESS	read-only
			STATUS	current
			::= { hmWanMbusE5 25 }

hmWanMbusE5VIF0A		OBJECT-TYPE
			SYNTAX	INTEGER
			MAX-ACCESS	read-only
			STATUS	current
			::= { hmWanMbusE5 26 }

hmWanMbusE5Value0A		OBJECT-TYPE
			SYNTAX	INTEGER
			MAX-ACCESS	read-only
			STATUS	current
			::= { hmWanMbusE5 27 }

hmWanMbusE5VIF0B		OBJECT-TYPE
			SYNTAX	INTEGER
			MAX-ACCESS	read-only
			STATUS	current
			::= { hmWanMbusE5 28 }

hmWanMbusE5Value0B		OBJECT-TYPE
			SYNTAX	INTEGER
			MAX-ACCESS	read-only
			STATUS	current
			::= { hmWanMbusE5 29 }

hmWanMbusE5VIF0C		OBJECT-TYPE
			SYNTAX	INTEGER
			MAX-ACCESS	read-only
			STATUS	current
			::= { hmWanMbusE5 30 }

hmWanMbusE5Value0C		OBJECT-TYPE
			SYNTAX	INTEGER
			MAX-ACCESS	read-only
			STATUS	current
			::= { hmWanMbusE5 31 }

hmWanMbusE5VIF0D		OBJECT-TYPE
			SYNTAX	INTEGER
			MAX-ACCESS	read-only
			STATUS	current
			::= { hmWanMbusE5 32 }

hmWanMbusE5Value0D		OBJECT-TYPE
			SYNTAX	INTEGER
			MAX-ACCESS	read-only
			STATUS	current
			::= { hmWanMbusE5 33 }

hmWanMbusE5VIF0E		OBJECT-TYPE
			SYNTAX	INTEGER
			MAX-ACCESS	read-only
			STATUS	current
			::= { hmWanMbusE5 34 }

hmWanMbusE5Value0E		OBJECT-TYPE
			SYNTAX	INTEGER
			MAX-ACCESS	read-only
			STATUS	current
			::= { hmWanMbusE5 35 }

hmWanMbusE5VIF0F		OBJECT-TYPE
			SYNTAX	INTEGER
			MAX-ACCESS	read-only
			STATUS	current
			::= { hmWanMbusE5 36 }

hmWanMbusE5Value0F		OBJECT-TYPE
			SYNTAX	INTEGER
			MAX-ACCESS	read-only
			STATUS	current
			::= { hmWanMbusE5 37 }

hmWanMbusE5VIF10		OBJECT-TYPE
			SYNTAX	INTEGER
			MAX-ACCESS	read-only
			STATUS	current
			::= { hmWanMbusE5 38 }

hmWanMbusE5Value10		OBJECT-TYPE
			SYNTAX	INTEGER
			MAX-ACCESS	read-only
			STATUS	current
			::= { hmWanMbusE5 39 }

hmWanMbusE5VIF11		OBJECT-TYPE
			SYNTAX	INTEGER
			MAX-ACCESS	read-only
			STATUS	current
			::= { hmWanMbusE5 40 }

hmWanMbusE5Value11		OBJECT-TYPE
			SYNTAX	INTEGER
			MAX-ACCESS	read-only
			STATUS	current
			::= { hmWanMbusE5 41 }

hmWanMbusE5VIF12		OBJECT-TYPE
			SYNTAX	INTEGER
			MAX-ACCESS	read-only
			STATUS	current
			::= { hmWanMbusE5 42 }

hmWanMbusE5Value12		OBJECT-TYPE
			SYNTAX	INTEGER
			MAX-ACCESS	read-only
			STATUS	current
			::= { hmWanMbusE5 43 }

hmWanMbusE5VIF13		OBJECT-TYPE
			SYNTAX	INTEGER
			MAX-ACCESS	read-only
			STATUS	current
			::= { hmWanMbusE5 44 }

hmWanMbusE5Value13		OBJECT-TYPE
			SYNTAX	INTEGER
			MAX-ACCESS	read-only
			STATUS	current
			::= { hmWanMbusE5 45 }

hmWanMbusE5VIF14		OBJECT-TYPE
			SYNTAX	INTEGER
			MAX-ACCESS	read-only
			STATUS	current
			::= { hmWanMbusE5 46 }

hmWanMbusE5Value14		OBJECT-TYPE
			SYNTAX	INTEGER
			MAX-ACCESS	read-only
			STATUS	current
			::= { hmWanMbusE5 47 }

hmWanMbusE5VIF15		OBJECT-TYPE
			SYNTAX	INTEGER
			MAX-ACCESS	read-only
			STATUS	current
			::= { hmWanMbusE5 48 }

hmWanMbusE5Value15		OBJECT-TYPE
			SYNTAX	INTEGER
			MAX-ACCESS	read-only
			STATUS	current
			::= { hmWanMbusE5 49 }

hmWanMbusE5VIF16		OBJECT-TYPE
			SYNTAX	INTEGER
			MAX-ACCESS	read-only
			STATUS	current
			::= { hmWanMbusE5 50 }

hmWanMbusE5Value16		OBJECT-TYPE
			SYNTAX	INTEGER
			MAX-ACCESS	read-only
			STATUS	current
			::= { hmWanMbusE5 51 }

hmWanMbusE5VIF17		OBJECT-TYPE
			SYNTAX	INTEGER
			MAX-ACCESS	read-only
			STATUS	current
			::= { hmWanMbusE5 52 }

hmWanMbusE5Value17		OBJECT-TYPE
			SYNTAX	INTEGER
			MAX-ACCESS	read-only
			STATUS	current
			::= { hmWanMbusE5 53 }

hmWanMbusE5VIF18		OBJECT-TYPE
			SYNTAX	INTEGER
			MAX-ACCESS	read-only
			STATUS	current
			::= { hmWanMbusE5 54 }

hmWanMbusE5Value18		OBJECT-TYPE
			SYNTAX	INTEGER
			MAX-ACCESS	read-only
			STATUS	current
			::= { hmWanMbusE5 55 }

hmWanMbusE5VIF19		OBJECT-TYPE
			SYNTAX	INTEGER
			MAX-ACCESS	read-only
			STATUS	current
			::= { hmWanMbusE5 56 }

hmWanMbusE5Value19		OBJECT-TYPE
			SYNTAX	INTEGER
			MAX-ACCESS	read-only
			STATUS	current
			::= { hmWanMbusE5 57 }

hmWanMbusE5VIF1A		OBJECT-TYPE
			SYNTAX	INTEGER
			MAX-ACCESS	read-only
			STATUS	current
			::= { hmWanMbusE5 58 }

hmWanMbusE5Value1A		OBJECT-TYPE
			SYNTAX	INTEGER
			MAX-ACCESS	read-only
			STATUS	current
			::= { hmWanMbusE5 59 }

hmWanMbusE5VIF1B		OBJECT-TYPE
			SYNTAX	INTEGER
			MAX-ACCESS	read-only
			STATUS	current
			::= { hmWanMbusE5 60 }

hmWanMbusE5Value1B		OBJECT-TYPE
			SYNTAX	INTEGER
			MAX-ACCESS	read-only
			STATUS	current
			::= { hmWanMbusE5 61 }

hmWanMbusE5VIF1C		OBJECT-TYPE
			SYNTAX	INTEGER
			MAX-ACCESS	read-only
			STATUS	current
			::= { hmWanMbusE5 62 }

hmWanMbusE5Value1C		OBJECT-TYPE
			SYNTAX	INTEGER
			MAX-ACCESS	read-only
			STATUS	current
			::= { hmWanMbusE5 63 }

hmWanMbusE5VIF1D		OBJECT-TYPE
			SYNTAX	INTEGER
			MAX-ACCESS	read-only
			STATUS	current
			::= { hmWanMbusE5 64 }

hmWanMbusE5Value1D		OBJECT-TYPE
			SYNTAX	INTEGER
			MAX-ACCESS	read-only
			STATUS	current
			::= { hmWanMbusE5 65 }

hmWanMbusE5VIF1E		OBJECT-TYPE
			SYNTAX	INTEGER
			MAX-ACCESS	read-only
			STATUS	current
			::= { hmWanMbusE5 66 }

hmWanMbusE5Value1E		OBJECT-TYPE
			SYNTAX	INTEGER
			MAX-ACCESS	read-only
			STATUS	current
			::= { hmWanMbusE5 67 }

hmWanMbusE5VIF1F		OBJECT-TYPE
			SYNTAX	INTEGER
			MAX-ACCESS	read-only
			STATUS	current
			::= { hmWanMbusE5 68 }

hmWanMbusE5Value1F		OBJECT-TYPE
			SYNTAX	INTEGER
			MAX-ACCESS	read-only
			STATUS	current
			::= { hmWanMbusE5 69 }

hmWanMbusE5VIF20		OBJECT-TYPE
			SYNTAX	INTEGER
			MAX-ACCESS	read-only
			STATUS	current
			::= { hmWanMbusE5 70 }

hmWanMbusE5Value20		OBJECT-TYPE
			SYNTAX	INTEGER
			MAX-ACCESS	read-only
			STATUS	current
			::= { hmWanMbusE5 71 }

hmWanMbusE5VIF21		OBJECT-TYPE
			SYNTAX	INTEGER
			MAX-ACCESS	read-only
			STATUS	current
			::= { hmWanMbusE5 72 }

hmWanMbusE5Value21		OBJECT-TYPE
			SYNTAX	INTEGER
			MAX-ACCESS	read-only
			STATUS	current
			::= { hmWanMbusE5 73 }

hmWanMbusE5VIF22		OBJECT-TYPE
			SYNTAX	INTEGER
			MAX-ACCESS	read-only
			STATUS	current
			::= { hmWanMbusE5 74 }

hmWanMbusE5Value22		OBJECT-TYPE
			SYNTAX	INTEGER
			MAX-ACCESS	read-only
			STATUS	current
			::= { hmWanMbusE5 75 }

hmWanMbusE5VIF23		OBJECT-TYPE
			SYNTAX	INTEGER
			MAX-ACCESS	read-only
			STATUS	current
			::= { hmWanMbusE5 76 }

hmWanMbusE5Value23		OBJECT-TYPE
			SYNTAX	INTEGER
			MAX-ACCESS	read-only
			STATUS	current
			::= { hmWanMbusE5 77 }

hmWanMbusE5VIF24		OBJECT-TYPE
			SYNTAX	INTEGER
			MAX-ACCESS	read-only
			STATUS	current
			::= { hmWanMbusE5 78 }

hmWanMbusE5Value24		OBJECT-TYPE
			SYNTAX	INTEGER
			MAX-ACCESS	read-only
			STATUS	current
			::= { hmWanMbusE5 79 }

hmWanMbusE5VIF25		OBJECT-TYPE
			SYNTAX	INTEGER
			MAX-ACCESS	read-only
			STATUS	current
			::= { hmWanMbusE5 80 }

hmWanMbusE5Value25		OBJECT-TYPE
			SYNTAX	INTEGER
			MAX-ACCESS	read-only
			STATUS	current
			::= { hmWanMbusE5 81 }

hmWanMbusE5VIF26		OBJECT-TYPE
			SYNTAX	INTEGER
			MAX-ACCESS	read-only
			STATUS	current
			::= { hmWanMbusE5 82 }

hmWanMbusE5Value26		OBJECT-TYPE
			SYNTAX	INTEGER
			MAX-ACCESS	read-only
			STATUS	current
			::= { hmWanMbusE5 83 }

hmWanMbusE5VIF27		OBJECT-TYPE
			SYNTAX	INTEGER
			MAX-ACCESS	read-only
			STATUS	current
			::= { hmWanMbusE5 84 }

hmWanMbusE5Value27		OBJECT-TYPE
			SYNTAX	INTEGER
			MAX-ACCESS	read-only
			STATUS	current
			::= { hmWanMbusE5 85 }

hmWanMbusE5VIF28		OBJECT-TYPE
			SYNTAX	INTEGER
			MAX-ACCESS	read-only
			STATUS	current
			::= { hmWanMbusE5 86 }

hmWanMbusE5Value28		OBJECT-TYPE
			SYNTAX	INTEGER
			MAX-ACCESS	read-only
			STATUS	current
			::= { hmWanMbusE5 87 }

hmWanMbusE5VIF29		OBJECT-TYPE
			SYNTAX	INTEGER
			MAX-ACCESS	read-only
			STATUS	current
			::= { hmWanMbusE5 88 }

hmWanMbusE5Value29		OBJECT-TYPE
			SYNTAX	INTEGER
			MAX-ACCESS	read-only
			STATUS	current
			::= { hmWanMbusE5 89 }

hmWanMbusE5VIF2A		OBJECT-TYPE
			SYNTAX	INTEGER
			MAX-ACCESS	read-only
			STATUS	current
			::= { hmWanMbusE5 90 }

hmWanMbusE5Value2A		OBJECT-TYPE
			SYNTAX	INTEGER
			MAX-ACCESS	read-only
			STATUS	current
			::= { hmWanMbusE5 91 }

hmWanMbusE5VIF2B		OBJECT-TYPE
			SYNTAX	INTEGER
			MAX-ACCESS	read-only
			STATUS	current
			::= { hmWanMbusE5 92 }

hmWanMbusE5Value2B		OBJECT-TYPE
			SYNTAX	INTEGER
			MAX-ACCESS	read-only
			STATUS	current
			::= { hmWanMbusE5 93 }

hmWanMbusE5VIF2C		OBJECT-TYPE
			SYNTAX	INTEGER
			MAX-ACCESS	read-only
			STATUS	current
			::= { hmWanMbusE5 94 }

hmWanMbusE5Value2C		OBJECT-TYPE
			SYNTAX	INTEGER
			MAX-ACCESS	read-only
			STATUS	current
			::= { hmWanMbusE5 95 }

hmWanMbusE5VIF2D		OBJECT-TYPE
			SYNTAX	INTEGER
			MAX-ACCESS	read-only
			STATUS	current
			::= { hmWanMbusE5 96 }

hmWanMbusE5Value2D		OBJECT-TYPE
			SYNTAX	INTEGER
			MAX-ACCESS	read-only
			STATUS	current
			::= { hmWanMbusE5 97 }

hmWanMbusE5VIF2E		OBJECT-TYPE
			SYNTAX	INTEGER
			MAX-ACCESS	read-only
			STATUS	current
			::= { hmWanMbusE5 98 }

hmWanMbusE5Value2E		OBJECT-TYPE
			SYNTAX	INTEGER
			MAX-ACCESS	read-only
			STATUS	current
			::= { hmWanMbusE5 99 }

hmWanMbusE5VIF2F		OBJECT-TYPE
			SYNTAX	INTEGER
			MAX-ACCESS	read-only
			STATUS	current
			::= { hmWanMbusE5 100 }

hmWanMbusE5Value2F		OBJECT-TYPE
			SYNTAX	INTEGER
			MAX-ACCESS	read-only
			STATUS	current
			::= { hmWanMbusE5 101 }

hmWanMbusE6			OBJECT IDENTIFIER ::= { hmWanMbus 230 }

hmWanMbusE6IdNumber		OBJECT-TYPE
			SYNTAX	Gauge32
			MAX-ACCESS	read-only
			STATUS	current
			::= { hmWanMbusE6 1 }

hmWanMbusE6Manufacturer	OBJECT-TYPE
			SYNTAX	Gauge32
			MAX-ACCESS	read-only
			STATUS	current
			::= { hmWanMbusE6 2 }

hmWanMbusE6Version		OBJECT-TYPE
			SYNTAX	Gauge32
			MAX-ACCESS	read-only
			STATUS	current
			::= { hmWanMbusE6 3 }

hmWanMbusE6Medium		OBJECT-TYPE
			SYNTAX	Gauge32
			MAX-ACCESS	read-only
			STATUS	current
			::= { hmWanMbusE6 4 }

hmWanMbusE6Status		OBJECT-TYPE
			SYNTAX	Gauge32
			MAX-ACCESS	read-only
			STATUS	current
			::= { hmWanMbusE6 5 }

hmWanMbusE6VIF00		OBJECT-TYPE
			SYNTAX	INTEGER
			MAX-ACCESS	read-only
			STATUS	current
			::= { hmWanMbusE6 6 }

hmWanMbusE6Value00		OBJECT-TYPE
			SYNTAX	INTEGER
			MAX-ACCESS	read-only
			STATUS	current
			::= { hmWanMbusE6 7 }

hmWanMbusE6VIF01		OBJECT-TYPE
			SYNTAX	INTEGER
			MAX-ACCESS	read-only
			STATUS	current
			::= { hmWanMbusE6 8 }

hmWanMbusE6Value01		OBJECT-TYPE
			SYNTAX	INTEGER
			MAX-ACCESS	read-only
			STATUS	current
			::= { hmWanMbusE6 9 }

hmWanMbusE6VIF02		OBJECT-TYPE
			SYNTAX	INTEGER
			MAX-ACCESS	read-only
			STATUS	current
			::= { hmWanMbusE6 10 }

hmWanMbusE6Value02		OBJECT-TYPE
			SYNTAX	INTEGER
			MAX-ACCESS	read-only
			STATUS	current
			::= { hmWanMbusE6 11 }

hmWanMbusE6VIF03		OBJECT-TYPE
			SYNTAX	INTEGER
			MAX-ACCESS	read-only
			STATUS	current
			::= { hmWanMbusE6 12 }

hmWanMbusE6Value03		OBJECT-TYPE
			SYNTAX	INTEGER
			MAX-ACCESS	read-only
			STATUS	current
			::= { hmWanMbusE6 13 }

hmWanMbusE6VIF04		OBJECT-TYPE
			SYNTAX	INTEGER
			MAX-ACCESS	read-only
			STATUS	current
			::= { hmWanMbusE6 14 }

hmWanMbusE6Value04		OBJECT-TYPE
			SYNTAX	INTEGER
			MAX-ACCESS	read-only
			STATUS	current
			::= { hmWanMbusE6 15 }

hmWanMbusE6VIF05		OBJECT-TYPE
			SYNTAX	INTEGER
			MAX-ACCESS	read-only
			STATUS	current
			::= { hmWanMbusE6 16 }

hmWanMbusE6Value05		OBJECT-TYPE
			SYNTAX	INTEGER
			MAX-ACCESS	read-only
			STATUS	current
			::= { hmWanMbusE6 17 }

hmWanMbusE6VIF06		OBJECT-TYPE
			SYNTAX	INTEGER
			MAX-ACCESS	read-only
			STATUS	current
			::= { hmWanMbusE6 18 }

hmWanMbusE6Value06		OBJECT-TYPE
			SYNTAX	INTEGER
			MAX-ACCESS	read-only
			STATUS	current
			::= { hmWanMbusE6 19 }

hmWanMbusE6VIF07		OBJECT-TYPE
			SYNTAX	INTEGER
			MAX-ACCESS	read-only
			STATUS	current
			::= { hmWanMbusE6 20 }

hmWanMbusE6Value07		OBJECT-TYPE
			SYNTAX	INTEGER
			MAX-ACCESS	read-only
			STATUS	current
			::= { hmWanMbusE6 21 }

hmWanMbusE6VIF08		OBJECT-TYPE
			SYNTAX	INTEGER
			MAX-ACCESS	read-only
			STATUS	current
			::= { hmWanMbusE6 22 }

hmWanMbusE6Value08		OBJECT-TYPE
			SYNTAX	INTEGER
			MAX-ACCESS	read-only
			STATUS	current
			::= { hmWanMbusE6 23 }

hmWanMbusE6VIF09		OBJECT-TYPE
			SYNTAX	INTEGER
			MAX-ACCESS	read-only
			STATUS	current
			::= { hmWanMbusE6 24 }

hmWanMbusE6Value09		OBJECT-TYPE
			SYNTAX	INTEGER
			MAX-ACCESS	read-only
			STATUS	current
			::= { hmWanMbusE6 25 }

hmWanMbusE6VIF0A		OBJECT-TYPE
			SYNTAX	INTEGER
			MAX-ACCESS	read-only
			STATUS	current
			::= { hmWanMbusE6 26 }

hmWanMbusE6Value0A		OBJECT-TYPE
			SYNTAX	INTEGER
			MAX-ACCESS	read-only
			STATUS	current
			::= { hmWanMbusE6 27 }

hmWanMbusE6VIF0B		OBJECT-TYPE
			SYNTAX	INTEGER
			MAX-ACCESS	read-only
			STATUS	current
			::= { hmWanMbusE6 28 }

hmWanMbusE6Value0B		OBJECT-TYPE
			SYNTAX	INTEGER
			MAX-ACCESS	read-only
			STATUS	current
			::= { hmWanMbusE6 29 }

hmWanMbusE6VIF0C		OBJECT-TYPE
			SYNTAX	INTEGER
			MAX-ACCESS	read-only
			STATUS	current
			::= { hmWanMbusE6 30 }

hmWanMbusE6Value0C		OBJECT-TYPE
			SYNTAX	INTEGER
			MAX-ACCESS	read-only
			STATUS	current
			::= { hmWanMbusE6 31 }

hmWanMbusE6VIF0D		OBJECT-TYPE
			SYNTAX	INTEGER
			MAX-ACCESS	read-only
			STATUS	current
			::= { hmWanMbusE6 32 }

hmWanMbusE6Value0D		OBJECT-TYPE
			SYNTAX	INTEGER
			MAX-ACCESS	read-only
			STATUS	current
			::= { hmWanMbusE6 33 }

hmWanMbusE6VIF0E		OBJECT-TYPE
			SYNTAX	INTEGER
			MAX-ACCESS	read-only
			STATUS	current
			::= { hmWanMbusE6 34 }

hmWanMbusE6Value0E		OBJECT-TYPE
			SYNTAX	INTEGER
			MAX-ACCESS	read-only
			STATUS	current
			::= { hmWanMbusE6 35 }

hmWanMbusE6VIF0F		OBJECT-TYPE
			SYNTAX	INTEGER
			MAX-ACCESS	read-only
			STATUS	current
			::= { hmWanMbusE6 36 }

hmWanMbusE6Value0F		OBJECT-TYPE
			SYNTAX	INTEGER
			MAX-ACCESS	read-only
			STATUS	current
			::= { hmWanMbusE6 37 }

hmWanMbusE6VIF10		OBJECT-TYPE
			SYNTAX	INTEGER
			MAX-ACCESS	read-only
			STATUS	current
			::= { hmWanMbusE6 38 }

hmWanMbusE6Value10		OBJECT-TYPE
			SYNTAX	INTEGER
			MAX-ACCESS	read-only
			STATUS	current
			::= { hmWanMbusE6 39 }

hmWanMbusE6VIF11		OBJECT-TYPE
			SYNTAX	INTEGER
			MAX-ACCESS	read-only
			STATUS	current
			::= { hmWanMbusE6 40 }

hmWanMbusE6Value11		OBJECT-TYPE
			SYNTAX	INTEGER
			MAX-ACCESS	read-only
			STATUS	current
			::= { hmWanMbusE6 41 }

hmWanMbusE6VIF12		OBJECT-TYPE
			SYNTAX	INTEGER
			MAX-ACCESS	read-only
			STATUS	current
			::= { hmWanMbusE6 42 }

hmWanMbusE6Value12		OBJECT-TYPE
			SYNTAX	INTEGER
			MAX-ACCESS	read-only
			STATUS	current
			::= { hmWanMbusE6 43 }

hmWanMbusE6VIF13		OBJECT-TYPE
			SYNTAX	INTEGER
			MAX-ACCESS	read-only
			STATUS	current
			::= { hmWanMbusE6 44 }

hmWanMbusE6Value13		OBJECT-TYPE
			SYNTAX	INTEGER
			MAX-ACCESS	read-only
			STATUS	current
			::= { hmWanMbusE6 45 }

hmWanMbusE6VIF14		OBJECT-TYPE
			SYNTAX	INTEGER
			MAX-ACCESS	read-only
			STATUS	current
			::= { hmWanMbusE6 46 }

hmWanMbusE6Value14		OBJECT-TYPE
			SYNTAX	INTEGER
			MAX-ACCESS	read-only
			STATUS	current
			::= { hmWanMbusE6 47 }

hmWanMbusE6VIF15		OBJECT-TYPE
			SYNTAX	INTEGER
			MAX-ACCESS	read-only
			STATUS	current
			::= { hmWanMbusE6 48 }

hmWanMbusE6Value15		OBJECT-TYPE
			SYNTAX	INTEGER
			MAX-ACCESS	read-only
			STATUS	current
			::= { hmWanMbusE6 49 }

hmWanMbusE6VIF16		OBJECT-TYPE
			SYNTAX	INTEGER
			MAX-ACCESS	read-only
			STATUS	current
			::= { hmWanMbusE6 50 }

hmWanMbusE6Value16		OBJECT-TYPE
			SYNTAX	INTEGER
			MAX-ACCESS	read-only
			STATUS	current
			::= { hmWanMbusE6 51 }

hmWanMbusE6VIF17		OBJECT-TYPE
			SYNTAX	INTEGER
			MAX-ACCESS	read-only
			STATUS	current
			::= { hmWanMbusE6 52 }

hmWanMbusE6Value17		OBJECT-TYPE
			SYNTAX	INTEGER
			MAX-ACCESS	read-only
			STATUS	current
			::= { hmWanMbusE6 53 }

hmWanMbusE6VIF18		OBJECT-TYPE
			SYNTAX	INTEGER
			MAX-ACCESS	read-only
			STATUS	current
			::= { hmWanMbusE6 54 }

hmWanMbusE6Value18		OBJECT-TYPE
			SYNTAX	INTEGER
			MAX-ACCESS	read-only
			STATUS	current
			::= { hmWanMbusE6 55 }

hmWanMbusE6VIF19		OBJECT-TYPE
			SYNTAX	INTEGER
			MAX-ACCESS	read-only
			STATUS	current
			::= { hmWanMbusE6 56 }

hmWanMbusE6Value19		OBJECT-TYPE
			SYNTAX	INTEGER
			MAX-ACCESS	read-only
			STATUS	current
			::= { hmWanMbusE6 57 }

hmWanMbusE6VIF1A		OBJECT-TYPE
			SYNTAX	INTEGER
			MAX-ACCESS	read-only
			STATUS	current
			::= { hmWanMbusE6 58 }

hmWanMbusE6Value1A		OBJECT-TYPE
			SYNTAX	INTEGER
			MAX-ACCESS	read-only
			STATUS	current
			::= { hmWanMbusE6 59 }

hmWanMbusE6VIF1B		OBJECT-TYPE
			SYNTAX	INTEGER
			MAX-ACCESS	read-only
			STATUS	current
			::= { hmWanMbusE6 60 }

hmWanMbusE6Value1B		OBJECT-TYPE
			SYNTAX	INTEGER
			MAX-ACCESS	read-only
			STATUS	current
			::= { hmWanMbusE6 61 }

hmWanMbusE6VIF1C		OBJECT-TYPE
			SYNTAX	INTEGER
			MAX-ACCESS	read-only
			STATUS	current
			::= { hmWanMbusE6 62 }

hmWanMbusE6Value1C		OBJECT-TYPE
			SYNTAX	INTEGER
			MAX-ACCESS	read-only
			STATUS	current
			::= { hmWanMbusE6 63 }

hmWanMbusE6VIF1D		OBJECT-TYPE
			SYNTAX	INTEGER
			MAX-ACCESS	read-only
			STATUS	current
			::= { hmWanMbusE6 64 }

hmWanMbusE6Value1D		OBJECT-TYPE
			SYNTAX	INTEGER
			MAX-ACCESS	read-only
			STATUS	current
			::= { hmWanMbusE6 65 }

hmWanMbusE6VIF1E		OBJECT-TYPE
			SYNTAX	INTEGER
			MAX-ACCESS	read-only
			STATUS	current
			::= { hmWanMbusE6 66 }

hmWanMbusE6Value1E		OBJECT-TYPE
			SYNTAX	INTEGER
			MAX-ACCESS	read-only
			STATUS	current
			::= { hmWanMbusE6 67 }

hmWanMbusE6VIF1F		OBJECT-TYPE
			SYNTAX	INTEGER
			MAX-ACCESS	read-only
			STATUS	current
			::= { hmWanMbusE6 68 }

hmWanMbusE6Value1F		OBJECT-TYPE
			SYNTAX	INTEGER
			MAX-ACCESS	read-only
			STATUS	current
			::= { hmWanMbusE6 69 }

hmWanMbusE6VIF20		OBJECT-TYPE
			SYNTAX	INTEGER
			MAX-ACCESS	read-only
			STATUS	current
			::= { hmWanMbusE6 70 }

hmWanMbusE6Value20		OBJECT-TYPE
			SYNTAX	INTEGER
			MAX-ACCESS	read-only
			STATUS	current
			::= { hmWanMbusE6 71 }

hmWanMbusE6VIF21		OBJECT-TYPE
			SYNTAX	INTEGER
			MAX-ACCESS	read-only
			STATUS	current
			::= { hmWanMbusE6 72 }

hmWanMbusE6Value21		OBJECT-TYPE
			SYNTAX	INTEGER
			MAX-ACCESS	read-only
			STATUS	current
			::= { hmWanMbusE6 73 }

hmWanMbusE6VIF22		OBJECT-TYPE
			SYNTAX	INTEGER
			MAX-ACCESS	read-only
			STATUS	current
			::= { hmWanMbusE6 74 }

hmWanMbusE6Value22		OBJECT-TYPE
			SYNTAX	INTEGER
			MAX-ACCESS	read-only
			STATUS	current
			::= { hmWanMbusE6 75 }

hmWanMbusE6VIF23		OBJECT-TYPE
			SYNTAX	INTEGER
			MAX-ACCESS	read-only
			STATUS	current
			::= { hmWanMbusE6 76 }

hmWanMbusE6Value23		OBJECT-TYPE
			SYNTAX	INTEGER
			MAX-ACCESS	read-only
			STATUS	current
			::= { hmWanMbusE6 77 }

hmWanMbusE6VIF24		OBJECT-TYPE
			SYNTAX	INTEGER
			MAX-ACCESS	read-only
			STATUS	current
			::= { hmWanMbusE6 78 }

hmWanMbusE6Value24		OBJECT-TYPE
			SYNTAX	INTEGER
			MAX-ACCESS	read-only
			STATUS	current
			::= { hmWanMbusE6 79 }

hmWanMbusE6VIF25		OBJECT-TYPE
			SYNTAX	INTEGER
			MAX-ACCESS	read-only
			STATUS	current
			::= { hmWanMbusE6 80 }

hmWanMbusE6Value25		OBJECT-TYPE
			SYNTAX	INTEGER
			MAX-ACCESS	read-only
			STATUS	current
			::= { hmWanMbusE6 81 }

hmWanMbusE6VIF26		OBJECT-TYPE
			SYNTAX	INTEGER
			MAX-ACCESS	read-only
			STATUS	current
			::= { hmWanMbusE6 82 }

hmWanMbusE6Value26		OBJECT-TYPE
			SYNTAX	INTEGER
			MAX-ACCESS	read-only
			STATUS	current
			::= { hmWanMbusE6 83 }

hmWanMbusE6VIF27		OBJECT-TYPE
			SYNTAX	INTEGER
			MAX-ACCESS	read-only
			STATUS	current
			::= { hmWanMbusE6 84 }

hmWanMbusE6Value27		OBJECT-TYPE
			SYNTAX	INTEGER
			MAX-ACCESS	read-only
			STATUS	current
			::= { hmWanMbusE6 85 }

hmWanMbusE6VIF28		OBJECT-TYPE
			SYNTAX	INTEGER
			MAX-ACCESS	read-only
			STATUS	current
			::= { hmWanMbusE6 86 }

hmWanMbusE6Value28		OBJECT-TYPE
			SYNTAX	INTEGER
			MAX-ACCESS	read-only
			STATUS	current
			::= { hmWanMbusE6 87 }

hmWanMbusE6VIF29		OBJECT-TYPE
			SYNTAX	INTEGER
			MAX-ACCESS	read-only
			STATUS	current
			::= { hmWanMbusE6 88 }

hmWanMbusE6Value29		OBJECT-TYPE
			SYNTAX	INTEGER
			MAX-ACCESS	read-only
			STATUS	current
			::= { hmWanMbusE6 89 }

hmWanMbusE6VIF2A		OBJECT-TYPE
			SYNTAX	INTEGER
			MAX-ACCESS	read-only
			STATUS	current
			::= { hmWanMbusE6 90 }

hmWanMbusE6Value2A		OBJECT-TYPE
			SYNTAX	INTEGER
			MAX-ACCESS	read-only
			STATUS	current
			::= { hmWanMbusE6 91 }

hmWanMbusE6VIF2B		OBJECT-TYPE
			SYNTAX	INTEGER
			MAX-ACCESS	read-only
			STATUS	current
			::= { hmWanMbusE6 92 }

hmWanMbusE6Value2B		OBJECT-TYPE
			SYNTAX	INTEGER
			MAX-ACCESS	read-only
			STATUS	current
			::= { hmWanMbusE6 93 }

hmWanMbusE6VIF2C		OBJECT-TYPE
			SYNTAX	INTEGER
			MAX-ACCESS	read-only
			STATUS	current
			::= { hmWanMbusE6 94 }

hmWanMbusE6Value2C		OBJECT-TYPE
			SYNTAX	INTEGER
			MAX-ACCESS	read-only
			STATUS	current
			::= { hmWanMbusE6 95 }

hmWanMbusE6VIF2D		OBJECT-TYPE
			SYNTAX	INTEGER
			MAX-ACCESS	read-only
			STATUS	current
			::= { hmWanMbusE6 96 }

hmWanMbusE6Value2D		OBJECT-TYPE
			SYNTAX	INTEGER
			MAX-ACCESS	read-only
			STATUS	current
			::= { hmWanMbusE6 97 }

hmWanMbusE6VIF2E		OBJECT-TYPE
			SYNTAX	INTEGER
			MAX-ACCESS	read-only
			STATUS	current
			::= { hmWanMbusE6 98 }

hmWanMbusE6Value2E		OBJECT-TYPE
			SYNTAX	INTEGER
			MAX-ACCESS	read-only
			STATUS	current
			::= { hmWanMbusE6 99 }

hmWanMbusE6VIF2F		OBJECT-TYPE
			SYNTAX	INTEGER
			MAX-ACCESS	read-only
			STATUS	current
			::= { hmWanMbusE6 100 }

hmWanMbusE6Value2F		OBJECT-TYPE
			SYNTAX	INTEGER
			MAX-ACCESS	read-only
			STATUS	current
			::= { hmWanMbusE6 101 }

hmWanMbusE7			OBJECT IDENTIFIER ::= { hmWanMbus 231 }

hmWanMbusE7IdNumber		OBJECT-TYPE
			SYNTAX	Gauge32
			MAX-ACCESS	read-only
			STATUS	current
			::= { hmWanMbusE7 1 }

hmWanMbusE7Manufacturer	OBJECT-TYPE
			SYNTAX	Gauge32
			MAX-ACCESS	read-only
			STATUS	current
			::= { hmWanMbusE7 2 }

hmWanMbusE7Version		OBJECT-TYPE
			SYNTAX	Gauge32
			MAX-ACCESS	read-only
			STATUS	current
			::= { hmWanMbusE7 3 }

hmWanMbusE7Medium		OBJECT-TYPE
			SYNTAX	Gauge32
			MAX-ACCESS	read-only
			STATUS	current
			::= { hmWanMbusE7 4 }

hmWanMbusE7Status		OBJECT-TYPE
			SYNTAX	Gauge32
			MAX-ACCESS	read-only
			STATUS	current
			::= { hmWanMbusE7 5 }

hmWanMbusE7VIF00		OBJECT-TYPE
			SYNTAX	INTEGER
			MAX-ACCESS	read-only
			STATUS	current
			::= { hmWanMbusE7 6 }

hmWanMbusE7Value00		OBJECT-TYPE
			SYNTAX	INTEGER
			MAX-ACCESS	read-only
			STATUS	current
			::= { hmWanMbusE7 7 }

hmWanMbusE7VIF01		OBJECT-TYPE
			SYNTAX	INTEGER
			MAX-ACCESS	read-only
			STATUS	current
			::= { hmWanMbusE7 8 }

hmWanMbusE7Value01		OBJECT-TYPE
			SYNTAX	INTEGER
			MAX-ACCESS	read-only
			STATUS	current
			::= { hmWanMbusE7 9 }

hmWanMbusE7VIF02		OBJECT-TYPE
			SYNTAX	INTEGER
			MAX-ACCESS	read-only
			STATUS	current
			::= { hmWanMbusE7 10 }

hmWanMbusE7Value02		OBJECT-TYPE
			SYNTAX	INTEGER
			MAX-ACCESS	read-only
			STATUS	current
			::= { hmWanMbusE7 11 }

hmWanMbusE7VIF03		OBJECT-TYPE
			SYNTAX	INTEGER
			MAX-ACCESS	read-only
			STATUS	current
			::= { hmWanMbusE7 12 }

hmWanMbusE7Value03		OBJECT-TYPE
			SYNTAX	INTEGER
			MAX-ACCESS	read-only
			STATUS	current
			::= { hmWanMbusE7 13 }

hmWanMbusE7VIF04		OBJECT-TYPE
			SYNTAX	INTEGER
			MAX-ACCESS	read-only
			STATUS	current
			::= { hmWanMbusE7 14 }

hmWanMbusE7Value04		OBJECT-TYPE
			SYNTAX	INTEGER
			MAX-ACCESS	read-only
			STATUS	current
			::= { hmWanMbusE7 15 }

hmWanMbusE7VIF05		OBJECT-TYPE
			SYNTAX	INTEGER
			MAX-ACCESS	read-only
			STATUS	current
			::= { hmWanMbusE7 16 }

hmWanMbusE7Value05		OBJECT-TYPE
			SYNTAX	INTEGER
			MAX-ACCESS	read-only
			STATUS	current
			::= { hmWanMbusE7 17 }

hmWanMbusE7VIF06		OBJECT-TYPE
			SYNTAX	INTEGER
			MAX-ACCESS	read-only
			STATUS	current
			::= { hmWanMbusE7 18 }

hmWanMbusE7Value06		OBJECT-TYPE
			SYNTAX	INTEGER
			MAX-ACCESS	read-only
			STATUS	current
			::= { hmWanMbusE7 19 }

hmWanMbusE7VIF07		OBJECT-TYPE
			SYNTAX	INTEGER
			MAX-ACCESS	read-only
			STATUS	current
			::= { hmWanMbusE7 20 }

hmWanMbusE7Value07		OBJECT-TYPE
			SYNTAX	INTEGER
			MAX-ACCESS	read-only
			STATUS	current
			::= { hmWanMbusE7 21 }

hmWanMbusE7VIF08		OBJECT-TYPE
			SYNTAX	INTEGER
			MAX-ACCESS	read-only
			STATUS	current
			::= { hmWanMbusE7 22 }

hmWanMbusE7Value08		OBJECT-TYPE
			SYNTAX	INTEGER
			MAX-ACCESS	read-only
			STATUS	current
			::= { hmWanMbusE7 23 }

hmWanMbusE7VIF09		OBJECT-TYPE
			SYNTAX	INTEGER
			MAX-ACCESS	read-only
			STATUS	current
			::= { hmWanMbusE7 24 }

hmWanMbusE7Value09		OBJECT-TYPE
			SYNTAX	INTEGER
			MAX-ACCESS	read-only
			STATUS	current
			::= { hmWanMbusE7 25 }

hmWanMbusE7VIF0A		OBJECT-TYPE
			SYNTAX	INTEGER
			MAX-ACCESS	read-only
			STATUS	current
			::= { hmWanMbusE7 26 }

hmWanMbusE7Value0A		OBJECT-TYPE
			SYNTAX	INTEGER
			MAX-ACCESS	read-only
			STATUS	current
			::= { hmWanMbusE7 27 }

hmWanMbusE7VIF0B		OBJECT-TYPE
			SYNTAX	INTEGER
			MAX-ACCESS	read-only
			STATUS	current
			::= { hmWanMbusE7 28 }

hmWanMbusE7Value0B		OBJECT-TYPE
			SYNTAX	INTEGER
			MAX-ACCESS	read-only
			STATUS	current
			::= { hmWanMbusE7 29 }

hmWanMbusE7VIF0C		OBJECT-TYPE
			SYNTAX	INTEGER
			MAX-ACCESS	read-only
			STATUS	current
			::= { hmWanMbusE7 30 }

hmWanMbusE7Value0C		OBJECT-TYPE
			SYNTAX	INTEGER
			MAX-ACCESS	read-only
			STATUS	current
			::= { hmWanMbusE7 31 }

hmWanMbusE7VIF0D		OBJECT-TYPE
			SYNTAX	INTEGER
			MAX-ACCESS	read-only
			STATUS	current
			::= { hmWanMbusE7 32 }

hmWanMbusE7Value0D		OBJECT-TYPE
			SYNTAX	INTEGER
			MAX-ACCESS	read-only
			STATUS	current
			::= { hmWanMbusE7 33 }

hmWanMbusE7VIF0E		OBJECT-TYPE
			SYNTAX	INTEGER
			MAX-ACCESS	read-only
			STATUS	current
			::= { hmWanMbusE7 34 }

hmWanMbusE7Value0E		OBJECT-TYPE
			SYNTAX	INTEGER
			MAX-ACCESS	read-only
			STATUS	current
			::= { hmWanMbusE7 35 }

hmWanMbusE7VIF0F		OBJECT-TYPE
			SYNTAX	INTEGER
			MAX-ACCESS	read-only
			STATUS	current
			::= { hmWanMbusE7 36 }

hmWanMbusE7Value0F		OBJECT-TYPE
			SYNTAX	INTEGER
			MAX-ACCESS	read-only
			STATUS	current
			::= { hmWanMbusE7 37 }

hmWanMbusE7VIF10		OBJECT-TYPE
			SYNTAX	INTEGER
			MAX-ACCESS	read-only
			STATUS	current
			::= { hmWanMbusE7 38 }

hmWanMbusE7Value10		OBJECT-TYPE
			SYNTAX	INTEGER
			MAX-ACCESS	read-only
			STATUS	current
			::= { hmWanMbusE7 39 }

hmWanMbusE7VIF11		OBJECT-TYPE
			SYNTAX	INTEGER
			MAX-ACCESS	read-only
			STATUS	current
			::= { hmWanMbusE7 40 }

hmWanMbusE7Value11		OBJECT-TYPE
			SYNTAX	INTEGER
			MAX-ACCESS	read-only
			STATUS	current
			::= { hmWanMbusE7 41 }

hmWanMbusE7VIF12		OBJECT-TYPE
			SYNTAX	INTEGER
			MAX-ACCESS	read-only
			STATUS	current
			::= { hmWanMbusE7 42 }

hmWanMbusE7Value12		OBJECT-TYPE
			SYNTAX	INTEGER
			MAX-ACCESS	read-only
			STATUS	current
			::= { hmWanMbusE7 43 }

hmWanMbusE7VIF13		OBJECT-TYPE
			SYNTAX	INTEGER
			MAX-ACCESS	read-only
			STATUS	current
			::= { hmWanMbusE7 44 }

hmWanMbusE7Value13		OBJECT-TYPE
			SYNTAX	INTEGER
			MAX-ACCESS	read-only
			STATUS	current
			::= { hmWanMbusE7 45 }

hmWanMbusE7VIF14		OBJECT-TYPE
			SYNTAX	INTEGER
			MAX-ACCESS	read-only
			STATUS	current
			::= { hmWanMbusE7 46 }

hmWanMbusE7Value14		OBJECT-TYPE
			SYNTAX	INTEGER
			MAX-ACCESS	read-only
			STATUS	current
			::= { hmWanMbusE7 47 }

hmWanMbusE7VIF15		OBJECT-TYPE
			SYNTAX	INTEGER
			MAX-ACCESS	read-only
			STATUS	current
			::= { hmWanMbusE7 48 }

hmWanMbusE7Value15		OBJECT-TYPE
			SYNTAX	INTEGER
			MAX-ACCESS	read-only
			STATUS	current
			::= { hmWanMbusE7 49 }

hmWanMbusE7VIF16		OBJECT-TYPE
			SYNTAX	INTEGER
			MAX-ACCESS	read-only
			STATUS	current
			::= { hmWanMbusE7 50 }

hmWanMbusE7Value16		OBJECT-TYPE
			SYNTAX	INTEGER
			MAX-ACCESS	read-only
			STATUS	current
			::= { hmWanMbusE7 51 }

hmWanMbusE7VIF17		OBJECT-TYPE
			SYNTAX	INTEGER
			MAX-ACCESS	read-only
			STATUS	current
			::= { hmWanMbusE7 52 }

hmWanMbusE7Value17		OBJECT-TYPE
			SYNTAX	INTEGER
			MAX-ACCESS	read-only
			STATUS	current
			::= { hmWanMbusE7 53 }

hmWanMbusE7VIF18		OBJECT-TYPE
			SYNTAX	INTEGER
			MAX-ACCESS	read-only
			STATUS	current
			::= { hmWanMbusE7 54 }

hmWanMbusE7Value18		OBJECT-TYPE
			SYNTAX	INTEGER
			MAX-ACCESS	read-only
			STATUS	current
			::= { hmWanMbusE7 55 }

hmWanMbusE7VIF19		OBJECT-TYPE
			SYNTAX	INTEGER
			MAX-ACCESS	read-only
			STATUS	current
			::= { hmWanMbusE7 56 }

hmWanMbusE7Value19		OBJECT-TYPE
			SYNTAX	INTEGER
			MAX-ACCESS	read-only
			STATUS	current
			::= { hmWanMbusE7 57 }

hmWanMbusE7VIF1A		OBJECT-TYPE
			SYNTAX	INTEGER
			MAX-ACCESS	read-only
			STATUS	current
			::= { hmWanMbusE7 58 }

hmWanMbusE7Value1A		OBJECT-TYPE
			SYNTAX	INTEGER
			MAX-ACCESS	read-only
			STATUS	current
			::= { hmWanMbusE7 59 }

hmWanMbusE7VIF1B		OBJECT-TYPE
			SYNTAX	INTEGER
			MAX-ACCESS	read-only
			STATUS	current
			::= { hmWanMbusE7 60 }

hmWanMbusE7Value1B		OBJECT-TYPE
			SYNTAX	INTEGER
			MAX-ACCESS	read-only
			STATUS	current
			::= { hmWanMbusE7 61 }

hmWanMbusE7VIF1C		OBJECT-TYPE
			SYNTAX	INTEGER
			MAX-ACCESS	read-only
			STATUS	current
			::= { hmWanMbusE7 62 }

hmWanMbusE7Value1C		OBJECT-TYPE
			SYNTAX	INTEGER
			MAX-ACCESS	read-only
			STATUS	current
			::= { hmWanMbusE7 63 }

hmWanMbusE7VIF1D		OBJECT-TYPE
			SYNTAX	INTEGER
			MAX-ACCESS	read-only
			STATUS	current
			::= { hmWanMbusE7 64 }

hmWanMbusE7Value1D		OBJECT-TYPE
			SYNTAX	INTEGER
			MAX-ACCESS	read-only
			STATUS	current
			::= { hmWanMbusE7 65 }

hmWanMbusE7VIF1E		OBJECT-TYPE
			SYNTAX	INTEGER
			MAX-ACCESS	read-only
			STATUS	current
			::= { hmWanMbusE7 66 }

hmWanMbusE7Value1E		OBJECT-TYPE
			SYNTAX	INTEGER
			MAX-ACCESS	read-only
			STATUS	current
			::= { hmWanMbusE7 67 }

hmWanMbusE7VIF1F		OBJECT-TYPE
			SYNTAX	INTEGER
			MAX-ACCESS	read-only
			STATUS	current
			::= { hmWanMbusE7 68 }

hmWanMbusE7Value1F		OBJECT-TYPE
			SYNTAX	INTEGER
			MAX-ACCESS	read-only
			STATUS	current
			::= { hmWanMbusE7 69 }

hmWanMbusE7VIF20		OBJECT-TYPE
			SYNTAX	INTEGER
			MAX-ACCESS	read-only
			STATUS	current
			::= { hmWanMbusE7 70 }

hmWanMbusE7Value20		OBJECT-TYPE
			SYNTAX	INTEGER
			MAX-ACCESS	read-only
			STATUS	current
			::= { hmWanMbusE7 71 }

hmWanMbusE7VIF21		OBJECT-TYPE
			SYNTAX	INTEGER
			MAX-ACCESS	read-only
			STATUS	current
			::= { hmWanMbusE7 72 }

hmWanMbusE7Value21		OBJECT-TYPE
			SYNTAX	INTEGER
			MAX-ACCESS	read-only
			STATUS	current
			::= { hmWanMbusE7 73 }

hmWanMbusE7VIF22		OBJECT-TYPE
			SYNTAX	INTEGER
			MAX-ACCESS	read-only
			STATUS	current
			::= { hmWanMbusE7 74 }

hmWanMbusE7Value22		OBJECT-TYPE
			SYNTAX	INTEGER
			MAX-ACCESS	read-only
			STATUS	current
			::= { hmWanMbusE7 75 }

hmWanMbusE7VIF23		OBJECT-TYPE
			SYNTAX	INTEGER
			MAX-ACCESS	read-only
			STATUS	current
			::= { hmWanMbusE7 76 }

hmWanMbusE7Value23		OBJECT-TYPE
			SYNTAX	INTEGER
			MAX-ACCESS	read-only
			STATUS	current
			::= { hmWanMbusE7 77 }

hmWanMbusE7VIF24		OBJECT-TYPE
			SYNTAX	INTEGER
			MAX-ACCESS	read-only
			STATUS	current
			::= { hmWanMbusE7 78 }

hmWanMbusE7Value24		OBJECT-TYPE
			SYNTAX	INTEGER
			MAX-ACCESS	read-only
			STATUS	current
			::= { hmWanMbusE7 79 }

hmWanMbusE7VIF25		OBJECT-TYPE
			SYNTAX	INTEGER
			MAX-ACCESS	read-only
			STATUS	current
			::= { hmWanMbusE7 80 }

hmWanMbusE7Value25		OBJECT-TYPE
			SYNTAX	INTEGER
			MAX-ACCESS	read-only
			STATUS	current
			::= { hmWanMbusE7 81 }

hmWanMbusE7VIF26		OBJECT-TYPE
			SYNTAX	INTEGER
			MAX-ACCESS	read-only
			STATUS	current
			::= { hmWanMbusE7 82 }

hmWanMbusE7Value26		OBJECT-TYPE
			SYNTAX	INTEGER
			MAX-ACCESS	read-only
			STATUS	current
			::= { hmWanMbusE7 83 }

hmWanMbusE7VIF27		OBJECT-TYPE
			SYNTAX	INTEGER
			MAX-ACCESS	read-only
			STATUS	current
			::= { hmWanMbusE7 84 }

hmWanMbusE7Value27		OBJECT-TYPE
			SYNTAX	INTEGER
			MAX-ACCESS	read-only
			STATUS	current
			::= { hmWanMbusE7 85 }

hmWanMbusE7VIF28		OBJECT-TYPE
			SYNTAX	INTEGER
			MAX-ACCESS	read-only
			STATUS	current
			::= { hmWanMbusE7 86 }

hmWanMbusE7Value28		OBJECT-TYPE
			SYNTAX	INTEGER
			MAX-ACCESS	read-only
			STATUS	current
			::= { hmWanMbusE7 87 }

hmWanMbusE7VIF29		OBJECT-TYPE
			SYNTAX	INTEGER
			MAX-ACCESS	read-only
			STATUS	current
			::= { hmWanMbusE7 88 }

hmWanMbusE7Value29		OBJECT-TYPE
			SYNTAX	INTEGER
			MAX-ACCESS	read-only
			STATUS	current
			::= { hmWanMbusE7 89 }

hmWanMbusE7VIF2A		OBJECT-TYPE
			SYNTAX	INTEGER
			MAX-ACCESS	read-only
			STATUS	current
			::= { hmWanMbusE7 90 }

hmWanMbusE7Value2A		OBJECT-TYPE
			SYNTAX	INTEGER
			MAX-ACCESS	read-only
			STATUS	current
			::= { hmWanMbusE7 91 }

hmWanMbusE7VIF2B		OBJECT-TYPE
			SYNTAX	INTEGER
			MAX-ACCESS	read-only
			STATUS	current
			::= { hmWanMbusE7 92 }

hmWanMbusE7Value2B		OBJECT-TYPE
			SYNTAX	INTEGER
			MAX-ACCESS	read-only
			STATUS	current
			::= { hmWanMbusE7 93 }

hmWanMbusE7VIF2C		OBJECT-TYPE
			SYNTAX	INTEGER
			MAX-ACCESS	read-only
			STATUS	current
			::= { hmWanMbusE7 94 }

hmWanMbusE7Value2C		OBJECT-TYPE
			SYNTAX	INTEGER
			MAX-ACCESS	read-only
			STATUS	current
			::= { hmWanMbusE7 95 }

hmWanMbusE7VIF2D		OBJECT-TYPE
			SYNTAX	INTEGER
			MAX-ACCESS	read-only
			STATUS	current
			::= { hmWanMbusE7 96 }

hmWanMbusE7Value2D		OBJECT-TYPE
			SYNTAX	INTEGER
			MAX-ACCESS	read-only
			STATUS	current
			::= { hmWanMbusE7 97 }

hmWanMbusE7VIF2E		OBJECT-TYPE
			SYNTAX	INTEGER
			MAX-ACCESS	read-only
			STATUS	current
			::= { hmWanMbusE7 98 }

hmWanMbusE7Value2E		OBJECT-TYPE
			SYNTAX	INTEGER
			MAX-ACCESS	read-only
			STATUS	current
			::= { hmWanMbusE7 99 }

hmWanMbusE7VIF2F		OBJECT-TYPE
			SYNTAX	INTEGER
			MAX-ACCESS	read-only
			STATUS	current
			::= { hmWanMbusE7 100 }

hmWanMbusE7Value2F		OBJECT-TYPE
			SYNTAX	INTEGER
			MAX-ACCESS	read-only
			STATUS	current
			::= { hmWanMbusE7 101 }

hmWanMbusE8			OBJECT IDENTIFIER ::= { hmWanMbus 232 }

hmWanMbusE8IdNumber		OBJECT-TYPE
			SYNTAX	Gauge32
			MAX-ACCESS	read-only
			STATUS	current
			::= { hmWanMbusE8 1 }

hmWanMbusE8Manufacturer	OBJECT-TYPE
			SYNTAX	Gauge32
			MAX-ACCESS	read-only
			STATUS	current
			::= { hmWanMbusE8 2 }

hmWanMbusE8Version		OBJECT-TYPE
			SYNTAX	Gauge32
			MAX-ACCESS	read-only
			STATUS	current
			::= { hmWanMbusE8 3 }

hmWanMbusE8Medium		OBJECT-TYPE
			SYNTAX	Gauge32
			MAX-ACCESS	read-only
			STATUS	current
			::= { hmWanMbusE8 4 }

hmWanMbusE8Status		OBJECT-TYPE
			SYNTAX	Gauge32
			MAX-ACCESS	read-only
			STATUS	current
			::= { hmWanMbusE8 5 }

hmWanMbusE8VIF00		OBJECT-TYPE
			SYNTAX	INTEGER
			MAX-ACCESS	read-only
			STATUS	current
			::= { hmWanMbusE8 6 }

hmWanMbusE8Value00		OBJECT-TYPE
			SYNTAX	INTEGER
			MAX-ACCESS	read-only
			STATUS	current
			::= { hmWanMbusE8 7 }

hmWanMbusE8VIF01		OBJECT-TYPE
			SYNTAX	INTEGER
			MAX-ACCESS	read-only
			STATUS	current
			::= { hmWanMbusE8 8 }

hmWanMbusE8Value01		OBJECT-TYPE
			SYNTAX	INTEGER
			MAX-ACCESS	read-only
			STATUS	current
			::= { hmWanMbusE8 9 }

hmWanMbusE8VIF02		OBJECT-TYPE
			SYNTAX	INTEGER
			MAX-ACCESS	read-only
			STATUS	current
			::= { hmWanMbusE8 10 }

hmWanMbusE8Value02		OBJECT-TYPE
			SYNTAX	INTEGER
			MAX-ACCESS	read-only
			STATUS	current
			::= { hmWanMbusE8 11 }

hmWanMbusE8VIF03		OBJECT-TYPE
			SYNTAX	INTEGER
			MAX-ACCESS	read-only
			STATUS	current
			::= { hmWanMbusE8 12 }

hmWanMbusE8Value03		OBJECT-TYPE
			SYNTAX	INTEGER
			MAX-ACCESS	read-only
			STATUS	current
			::= { hmWanMbusE8 13 }

hmWanMbusE8VIF04		OBJECT-TYPE
			SYNTAX	INTEGER
			MAX-ACCESS	read-only
			STATUS	current
			::= { hmWanMbusE8 14 }

hmWanMbusE8Value04		OBJECT-TYPE
			SYNTAX	INTEGER
			MAX-ACCESS	read-only
			STATUS	current
			::= { hmWanMbusE8 15 }

hmWanMbusE8VIF05		OBJECT-TYPE
			SYNTAX	INTEGER
			MAX-ACCESS	read-only
			STATUS	current
			::= { hmWanMbusE8 16 }

hmWanMbusE8Value05		OBJECT-TYPE
			SYNTAX	INTEGER
			MAX-ACCESS	read-only
			STATUS	current
			::= { hmWanMbusE8 17 }

hmWanMbusE8VIF06		OBJECT-TYPE
			SYNTAX	INTEGER
			MAX-ACCESS	read-only
			STATUS	current
			::= { hmWanMbusE8 18 }

hmWanMbusE8Value06		OBJECT-TYPE
			SYNTAX	INTEGER
			MAX-ACCESS	read-only
			STATUS	current
			::= { hmWanMbusE8 19 }

hmWanMbusE8VIF07		OBJECT-TYPE
			SYNTAX	INTEGER
			MAX-ACCESS	read-only
			STATUS	current
			::= { hmWanMbusE8 20 }

hmWanMbusE8Value07		OBJECT-TYPE
			SYNTAX	INTEGER
			MAX-ACCESS	read-only
			STATUS	current
			::= { hmWanMbusE8 21 }

hmWanMbusE8VIF08		OBJECT-TYPE
			SYNTAX	INTEGER
			MAX-ACCESS	read-only
			STATUS	current
			::= { hmWanMbusE8 22 }

hmWanMbusE8Value08		OBJECT-TYPE
			SYNTAX	INTEGER
			MAX-ACCESS	read-only
			STATUS	current
			::= { hmWanMbusE8 23 }

hmWanMbusE8VIF09		OBJECT-TYPE
			SYNTAX	INTEGER
			MAX-ACCESS	read-only
			STATUS	current
			::= { hmWanMbusE8 24 }

hmWanMbusE8Value09		OBJECT-TYPE
			SYNTAX	INTEGER
			MAX-ACCESS	read-only
			STATUS	current
			::= { hmWanMbusE8 25 }

hmWanMbusE8VIF0A		OBJECT-TYPE
			SYNTAX	INTEGER
			MAX-ACCESS	read-only
			STATUS	current
			::= { hmWanMbusE8 26 }

hmWanMbusE8Value0A		OBJECT-TYPE
			SYNTAX	INTEGER
			MAX-ACCESS	read-only
			STATUS	current
			::= { hmWanMbusE8 27 }

hmWanMbusE8VIF0B		OBJECT-TYPE
			SYNTAX	INTEGER
			MAX-ACCESS	read-only
			STATUS	current
			::= { hmWanMbusE8 28 }

hmWanMbusE8Value0B		OBJECT-TYPE
			SYNTAX	INTEGER
			MAX-ACCESS	read-only
			STATUS	current
			::= { hmWanMbusE8 29 }

hmWanMbusE8VIF0C		OBJECT-TYPE
			SYNTAX	INTEGER
			MAX-ACCESS	read-only
			STATUS	current
			::= { hmWanMbusE8 30 }

hmWanMbusE8Value0C		OBJECT-TYPE
			SYNTAX	INTEGER
			MAX-ACCESS	read-only
			STATUS	current
			::= { hmWanMbusE8 31 }

hmWanMbusE8VIF0D		OBJECT-TYPE
			SYNTAX	INTEGER
			MAX-ACCESS	read-only
			STATUS	current
			::= { hmWanMbusE8 32 }

hmWanMbusE8Value0D		OBJECT-TYPE
			SYNTAX	INTEGER
			MAX-ACCESS	read-only
			STATUS	current
			::= { hmWanMbusE8 33 }

hmWanMbusE8VIF0E		OBJECT-TYPE
			SYNTAX	INTEGER
			MAX-ACCESS	read-only
			STATUS	current
			::= { hmWanMbusE8 34 }

hmWanMbusE8Value0E		OBJECT-TYPE
			SYNTAX	INTEGER
			MAX-ACCESS	read-only
			STATUS	current
			::= { hmWanMbusE8 35 }

hmWanMbusE8VIF0F		OBJECT-TYPE
			SYNTAX	INTEGER
			MAX-ACCESS	read-only
			STATUS	current
			::= { hmWanMbusE8 36 }

hmWanMbusE8Value0F		OBJECT-TYPE
			SYNTAX	INTEGER
			MAX-ACCESS	read-only
			STATUS	current
			::= { hmWanMbusE8 37 }

hmWanMbusE8VIF10		OBJECT-TYPE
			SYNTAX	INTEGER
			MAX-ACCESS	read-only
			STATUS	current
			::= { hmWanMbusE8 38 }

hmWanMbusE8Value10		OBJECT-TYPE
			SYNTAX	INTEGER
			MAX-ACCESS	read-only
			STATUS	current
			::= { hmWanMbusE8 39 }

hmWanMbusE8VIF11		OBJECT-TYPE
			SYNTAX	INTEGER
			MAX-ACCESS	read-only
			STATUS	current
			::= { hmWanMbusE8 40 }

hmWanMbusE8Value11		OBJECT-TYPE
			SYNTAX	INTEGER
			MAX-ACCESS	read-only
			STATUS	current
			::= { hmWanMbusE8 41 }

hmWanMbusE8VIF12		OBJECT-TYPE
			SYNTAX	INTEGER
			MAX-ACCESS	read-only
			STATUS	current
			::= { hmWanMbusE8 42 }

hmWanMbusE8Value12		OBJECT-TYPE
			SYNTAX	INTEGER
			MAX-ACCESS	read-only
			STATUS	current
			::= { hmWanMbusE8 43 }

hmWanMbusE8VIF13		OBJECT-TYPE
			SYNTAX	INTEGER
			MAX-ACCESS	read-only
			STATUS	current
			::= { hmWanMbusE8 44 }

hmWanMbusE8Value13		OBJECT-TYPE
			SYNTAX	INTEGER
			MAX-ACCESS	read-only
			STATUS	current
			::= { hmWanMbusE8 45 }

hmWanMbusE8VIF14		OBJECT-TYPE
			SYNTAX	INTEGER
			MAX-ACCESS	read-only
			STATUS	current
			::= { hmWanMbusE8 46 }

hmWanMbusE8Value14		OBJECT-TYPE
			SYNTAX	INTEGER
			MAX-ACCESS	read-only
			STATUS	current
			::= { hmWanMbusE8 47 }

hmWanMbusE8VIF15		OBJECT-TYPE
			SYNTAX	INTEGER
			MAX-ACCESS	read-only
			STATUS	current
			::= { hmWanMbusE8 48 }

hmWanMbusE8Value15		OBJECT-TYPE
			SYNTAX	INTEGER
			MAX-ACCESS	read-only
			STATUS	current
			::= { hmWanMbusE8 49 }

hmWanMbusE8VIF16		OBJECT-TYPE
			SYNTAX	INTEGER
			MAX-ACCESS	read-only
			STATUS	current
			::= { hmWanMbusE8 50 }

hmWanMbusE8Value16		OBJECT-TYPE
			SYNTAX	INTEGER
			MAX-ACCESS	read-only
			STATUS	current
			::= { hmWanMbusE8 51 }

hmWanMbusE8VIF17		OBJECT-TYPE
			SYNTAX	INTEGER
			MAX-ACCESS	read-only
			STATUS	current
			::= { hmWanMbusE8 52 }

hmWanMbusE8Value17		OBJECT-TYPE
			SYNTAX	INTEGER
			MAX-ACCESS	read-only
			STATUS	current
			::= { hmWanMbusE8 53 }

hmWanMbusE8VIF18		OBJECT-TYPE
			SYNTAX	INTEGER
			MAX-ACCESS	read-only
			STATUS	current
			::= { hmWanMbusE8 54 }

hmWanMbusE8Value18		OBJECT-TYPE
			SYNTAX	INTEGER
			MAX-ACCESS	read-only
			STATUS	current
			::= { hmWanMbusE8 55 }

hmWanMbusE8VIF19		OBJECT-TYPE
			SYNTAX	INTEGER
			MAX-ACCESS	read-only
			STATUS	current
			::= { hmWanMbusE8 56 }

hmWanMbusE8Value19		OBJECT-TYPE
			SYNTAX	INTEGER
			MAX-ACCESS	read-only
			STATUS	current
			::= { hmWanMbusE8 57 }

hmWanMbusE8VIF1A		OBJECT-TYPE
			SYNTAX	INTEGER
			MAX-ACCESS	read-only
			STATUS	current
			::= { hmWanMbusE8 58 }

hmWanMbusE8Value1A		OBJECT-TYPE
			SYNTAX	INTEGER
			MAX-ACCESS	read-only
			STATUS	current
			::= { hmWanMbusE8 59 }

hmWanMbusE8VIF1B		OBJECT-TYPE
			SYNTAX	INTEGER
			MAX-ACCESS	read-only
			STATUS	current
			::= { hmWanMbusE8 60 }

hmWanMbusE8Value1B		OBJECT-TYPE
			SYNTAX	INTEGER
			MAX-ACCESS	read-only
			STATUS	current
			::= { hmWanMbusE8 61 }

hmWanMbusE8VIF1C		OBJECT-TYPE
			SYNTAX	INTEGER
			MAX-ACCESS	read-only
			STATUS	current
			::= { hmWanMbusE8 62 }

hmWanMbusE8Value1C		OBJECT-TYPE
			SYNTAX	INTEGER
			MAX-ACCESS	read-only
			STATUS	current
			::= { hmWanMbusE8 63 }

hmWanMbusE8VIF1D		OBJECT-TYPE
			SYNTAX	INTEGER
			MAX-ACCESS	read-only
			STATUS	current
			::= { hmWanMbusE8 64 }

hmWanMbusE8Value1D		OBJECT-TYPE
			SYNTAX	INTEGER
			MAX-ACCESS	read-only
			STATUS	current
			::= { hmWanMbusE8 65 }

hmWanMbusE8VIF1E		OBJECT-TYPE
			SYNTAX	INTEGER
			MAX-ACCESS	read-only
			STATUS	current
			::= { hmWanMbusE8 66 }

hmWanMbusE8Value1E		OBJECT-TYPE
			SYNTAX	INTEGER
			MAX-ACCESS	read-only
			STATUS	current
			::= { hmWanMbusE8 67 }

hmWanMbusE8VIF1F		OBJECT-TYPE
			SYNTAX	INTEGER
			MAX-ACCESS	read-only
			STATUS	current
			::= { hmWanMbusE8 68 }

hmWanMbusE8Value1F		OBJECT-TYPE
			SYNTAX	INTEGER
			MAX-ACCESS	read-only
			STATUS	current
			::= { hmWanMbusE8 69 }

hmWanMbusE8VIF20		OBJECT-TYPE
			SYNTAX	INTEGER
			MAX-ACCESS	read-only
			STATUS	current
			::= { hmWanMbusE8 70 }

hmWanMbusE8Value20		OBJECT-TYPE
			SYNTAX	INTEGER
			MAX-ACCESS	read-only
			STATUS	current
			::= { hmWanMbusE8 71 }

hmWanMbusE8VIF21		OBJECT-TYPE
			SYNTAX	INTEGER
			MAX-ACCESS	read-only
			STATUS	current
			::= { hmWanMbusE8 72 }

hmWanMbusE8Value21		OBJECT-TYPE
			SYNTAX	INTEGER
			MAX-ACCESS	read-only
			STATUS	current
			::= { hmWanMbusE8 73 }

hmWanMbusE8VIF22		OBJECT-TYPE
			SYNTAX	INTEGER
			MAX-ACCESS	read-only
			STATUS	current
			::= { hmWanMbusE8 74 }

hmWanMbusE8Value22		OBJECT-TYPE
			SYNTAX	INTEGER
			MAX-ACCESS	read-only
			STATUS	current
			::= { hmWanMbusE8 75 }

hmWanMbusE8VIF23		OBJECT-TYPE
			SYNTAX	INTEGER
			MAX-ACCESS	read-only
			STATUS	current
			::= { hmWanMbusE8 76 }

hmWanMbusE8Value23		OBJECT-TYPE
			SYNTAX	INTEGER
			MAX-ACCESS	read-only
			STATUS	current
			::= { hmWanMbusE8 77 }

hmWanMbusE8VIF24		OBJECT-TYPE
			SYNTAX	INTEGER
			MAX-ACCESS	read-only
			STATUS	current
			::= { hmWanMbusE8 78 }

hmWanMbusE8Value24		OBJECT-TYPE
			SYNTAX	INTEGER
			MAX-ACCESS	read-only
			STATUS	current
			::= { hmWanMbusE8 79 }

hmWanMbusE8VIF25		OBJECT-TYPE
			SYNTAX	INTEGER
			MAX-ACCESS	read-only
			STATUS	current
			::= { hmWanMbusE8 80 }

hmWanMbusE8Value25		OBJECT-TYPE
			SYNTAX	INTEGER
			MAX-ACCESS	read-only
			STATUS	current
			::= { hmWanMbusE8 81 }

hmWanMbusE8VIF26		OBJECT-TYPE
			SYNTAX	INTEGER
			MAX-ACCESS	read-only
			STATUS	current
			::= { hmWanMbusE8 82 }

hmWanMbusE8Value26		OBJECT-TYPE
			SYNTAX	INTEGER
			MAX-ACCESS	read-only
			STATUS	current
			::= { hmWanMbusE8 83 }

hmWanMbusE8VIF27		OBJECT-TYPE
			SYNTAX	INTEGER
			MAX-ACCESS	read-only
			STATUS	current
			::= { hmWanMbusE8 84 }

hmWanMbusE8Value27		OBJECT-TYPE
			SYNTAX	INTEGER
			MAX-ACCESS	read-only
			STATUS	current
			::= { hmWanMbusE8 85 }

hmWanMbusE8VIF28		OBJECT-TYPE
			SYNTAX	INTEGER
			MAX-ACCESS	read-only
			STATUS	current
			::= { hmWanMbusE8 86 }

hmWanMbusE8Value28		OBJECT-TYPE
			SYNTAX	INTEGER
			MAX-ACCESS	read-only
			STATUS	current
			::= { hmWanMbusE8 87 }

hmWanMbusE8VIF29		OBJECT-TYPE
			SYNTAX	INTEGER
			MAX-ACCESS	read-only
			STATUS	current
			::= { hmWanMbusE8 88 }

hmWanMbusE8Value29		OBJECT-TYPE
			SYNTAX	INTEGER
			MAX-ACCESS	read-only
			STATUS	current
			::= { hmWanMbusE8 89 }

hmWanMbusE8VIF2A		OBJECT-TYPE
			SYNTAX	INTEGER
			MAX-ACCESS	read-only
			STATUS	current
			::= { hmWanMbusE8 90 }

hmWanMbusE8Value2A		OBJECT-TYPE
			SYNTAX	INTEGER
			MAX-ACCESS	read-only
			STATUS	current
			::= { hmWanMbusE8 91 }

hmWanMbusE8VIF2B		OBJECT-TYPE
			SYNTAX	INTEGER
			MAX-ACCESS	read-only
			STATUS	current
			::= { hmWanMbusE8 92 }

hmWanMbusE8Value2B		OBJECT-TYPE
			SYNTAX	INTEGER
			MAX-ACCESS	read-only
			STATUS	current
			::= { hmWanMbusE8 93 }

hmWanMbusE8VIF2C		OBJECT-TYPE
			SYNTAX	INTEGER
			MAX-ACCESS	read-only
			STATUS	current
			::= { hmWanMbusE8 94 }

hmWanMbusE8Value2C		OBJECT-TYPE
			SYNTAX	INTEGER
			MAX-ACCESS	read-only
			STATUS	current
			::= { hmWanMbusE8 95 }

hmWanMbusE8VIF2D		OBJECT-TYPE
			SYNTAX	INTEGER
			MAX-ACCESS	read-only
			STATUS	current
			::= { hmWanMbusE8 96 }

hmWanMbusE8Value2D		OBJECT-TYPE
			SYNTAX	INTEGER
			MAX-ACCESS	read-only
			STATUS	current
			::= { hmWanMbusE8 97 }

hmWanMbusE8VIF2E		OBJECT-TYPE
			SYNTAX	INTEGER
			MAX-ACCESS	read-only
			STATUS	current
			::= { hmWanMbusE8 98 }

hmWanMbusE8Value2E		OBJECT-TYPE
			SYNTAX	INTEGER
			MAX-ACCESS	read-only
			STATUS	current
			::= { hmWanMbusE8 99 }

hmWanMbusE8VIF2F		OBJECT-TYPE
			SYNTAX	INTEGER
			MAX-ACCESS	read-only
			STATUS	current
			::= { hmWanMbusE8 100 }

hmWanMbusE8Value2F		OBJECT-TYPE
			SYNTAX	INTEGER
			MAX-ACCESS	read-only
			STATUS	current
			::= { hmWanMbusE8 101 }

hmWanMbusE9			OBJECT IDENTIFIER ::= { hmWanMbus 233 }

hmWanMbusE9IdNumber		OBJECT-TYPE
			SYNTAX	Gauge32
			MAX-ACCESS	read-only
			STATUS	current
			::= { hmWanMbusE9 1 }

hmWanMbusE9Manufacturer	OBJECT-TYPE
			SYNTAX	Gauge32
			MAX-ACCESS	read-only
			STATUS	current
			::= { hmWanMbusE9 2 }

hmWanMbusE9Version		OBJECT-TYPE
			SYNTAX	Gauge32
			MAX-ACCESS	read-only
			STATUS	current
			::= { hmWanMbusE9 3 }

hmWanMbusE9Medium		OBJECT-TYPE
			SYNTAX	Gauge32
			MAX-ACCESS	read-only
			STATUS	current
			::= { hmWanMbusE9 4 }

hmWanMbusE9Status		OBJECT-TYPE
			SYNTAX	Gauge32
			MAX-ACCESS	read-only
			STATUS	current
			::= { hmWanMbusE9 5 }

hmWanMbusE9VIF00		OBJECT-TYPE
			SYNTAX	INTEGER
			MAX-ACCESS	read-only
			STATUS	current
			::= { hmWanMbusE9 6 }

hmWanMbusE9Value00		OBJECT-TYPE
			SYNTAX	INTEGER
			MAX-ACCESS	read-only
			STATUS	current
			::= { hmWanMbusE9 7 }

hmWanMbusE9VIF01		OBJECT-TYPE
			SYNTAX	INTEGER
			MAX-ACCESS	read-only
			STATUS	current
			::= { hmWanMbusE9 8 }

hmWanMbusE9Value01		OBJECT-TYPE
			SYNTAX	INTEGER
			MAX-ACCESS	read-only
			STATUS	current
			::= { hmWanMbusE9 9 }

hmWanMbusE9VIF02		OBJECT-TYPE
			SYNTAX	INTEGER
			MAX-ACCESS	read-only
			STATUS	current
			::= { hmWanMbusE9 10 }

hmWanMbusE9Value02		OBJECT-TYPE
			SYNTAX	INTEGER
			MAX-ACCESS	read-only
			STATUS	current
			::= { hmWanMbusE9 11 }

hmWanMbusE9VIF03		OBJECT-TYPE
			SYNTAX	INTEGER
			MAX-ACCESS	read-only
			STATUS	current
			::= { hmWanMbusE9 12 }

hmWanMbusE9Value03		OBJECT-TYPE
			SYNTAX	INTEGER
			MAX-ACCESS	read-only
			STATUS	current
			::= { hmWanMbusE9 13 }

hmWanMbusE9VIF04		OBJECT-TYPE
			SYNTAX	INTEGER
			MAX-ACCESS	read-only
			STATUS	current
			::= { hmWanMbusE9 14 }

hmWanMbusE9Value04		OBJECT-TYPE
			SYNTAX	INTEGER
			MAX-ACCESS	read-only
			STATUS	current
			::= { hmWanMbusE9 15 }

hmWanMbusE9VIF05		OBJECT-TYPE
			SYNTAX	INTEGER
			MAX-ACCESS	read-only
			STATUS	current
			::= { hmWanMbusE9 16 }

hmWanMbusE9Value05		OBJECT-TYPE
			SYNTAX	INTEGER
			MAX-ACCESS	read-only
			STATUS	current
			::= { hmWanMbusE9 17 }

hmWanMbusE9VIF06		OBJECT-TYPE
			SYNTAX	INTEGER
			MAX-ACCESS	read-only
			STATUS	current
			::= { hmWanMbusE9 18 }

hmWanMbusE9Value06		OBJECT-TYPE
			SYNTAX	INTEGER
			MAX-ACCESS	read-only
			STATUS	current
			::= { hmWanMbusE9 19 }

hmWanMbusE9VIF07		OBJECT-TYPE
			SYNTAX	INTEGER
			MAX-ACCESS	read-only
			STATUS	current
			::= { hmWanMbusE9 20 }

hmWanMbusE9Value07		OBJECT-TYPE
			SYNTAX	INTEGER
			MAX-ACCESS	read-only
			STATUS	current
			::= { hmWanMbusE9 21 }

hmWanMbusE9VIF08		OBJECT-TYPE
			SYNTAX	INTEGER
			MAX-ACCESS	read-only
			STATUS	current
			::= { hmWanMbusE9 22 }

hmWanMbusE9Value08		OBJECT-TYPE
			SYNTAX	INTEGER
			MAX-ACCESS	read-only
			STATUS	current
			::= { hmWanMbusE9 23 }

hmWanMbusE9VIF09		OBJECT-TYPE
			SYNTAX	INTEGER
			MAX-ACCESS	read-only
			STATUS	current
			::= { hmWanMbusE9 24 }

hmWanMbusE9Value09		OBJECT-TYPE
			SYNTAX	INTEGER
			MAX-ACCESS	read-only
			STATUS	current
			::= { hmWanMbusE9 25 }

hmWanMbusE9VIF0A		OBJECT-TYPE
			SYNTAX	INTEGER
			MAX-ACCESS	read-only
			STATUS	current
			::= { hmWanMbusE9 26 }

hmWanMbusE9Value0A		OBJECT-TYPE
			SYNTAX	INTEGER
			MAX-ACCESS	read-only
			STATUS	current
			::= { hmWanMbusE9 27 }

hmWanMbusE9VIF0B		OBJECT-TYPE
			SYNTAX	INTEGER
			MAX-ACCESS	read-only
			STATUS	current
			::= { hmWanMbusE9 28 }

hmWanMbusE9Value0B		OBJECT-TYPE
			SYNTAX	INTEGER
			MAX-ACCESS	read-only
			STATUS	current
			::= { hmWanMbusE9 29 }

hmWanMbusE9VIF0C		OBJECT-TYPE
			SYNTAX	INTEGER
			MAX-ACCESS	read-only
			STATUS	current
			::= { hmWanMbusE9 30 }

hmWanMbusE9Value0C		OBJECT-TYPE
			SYNTAX	INTEGER
			MAX-ACCESS	read-only
			STATUS	current
			::= { hmWanMbusE9 31 }

hmWanMbusE9VIF0D		OBJECT-TYPE
			SYNTAX	INTEGER
			MAX-ACCESS	read-only
			STATUS	current
			::= { hmWanMbusE9 32 }

hmWanMbusE9Value0D		OBJECT-TYPE
			SYNTAX	INTEGER
			MAX-ACCESS	read-only
			STATUS	current
			::= { hmWanMbusE9 33 }

hmWanMbusE9VIF0E		OBJECT-TYPE
			SYNTAX	INTEGER
			MAX-ACCESS	read-only
			STATUS	current
			::= { hmWanMbusE9 34 }

hmWanMbusE9Value0E		OBJECT-TYPE
			SYNTAX	INTEGER
			MAX-ACCESS	read-only
			STATUS	current
			::= { hmWanMbusE9 35 }

hmWanMbusE9VIF0F		OBJECT-TYPE
			SYNTAX	INTEGER
			MAX-ACCESS	read-only
			STATUS	current
			::= { hmWanMbusE9 36 }

hmWanMbusE9Value0F		OBJECT-TYPE
			SYNTAX	INTEGER
			MAX-ACCESS	read-only
			STATUS	current
			::= { hmWanMbusE9 37 }

hmWanMbusE9VIF10		OBJECT-TYPE
			SYNTAX	INTEGER
			MAX-ACCESS	read-only
			STATUS	current
			::= { hmWanMbusE9 38 }

hmWanMbusE9Value10		OBJECT-TYPE
			SYNTAX	INTEGER
			MAX-ACCESS	read-only
			STATUS	current
			::= { hmWanMbusE9 39 }

hmWanMbusE9VIF11		OBJECT-TYPE
			SYNTAX	INTEGER
			MAX-ACCESS	read-only
			STATUS	current
			::= { hmWanMbusE9 40 }

hmWanMbusE9Value11		OBJECT-TYPE
			SYNTAX	INTEGER
			MAX-ACCESS	read-only
			STATUS	current
			::= { hmWanMbusE9 41 }

hmWanMbusE9VIF12		OBJECT-TYPE
			SYNTAX	INTEGER
			MAX-ACCESS	read-only
			STATUS	current
			::= { hmWanMbusE9 42 }

hmWanMbusE9Value12		OBJECT-TYPE
			SYNTAX	INTEGER
			MAX-ACCESS	read-only
			STATUS	current
			::= { hmWanMbusE9 43 }

hmWanMbusE9VIF13		OBJECT-TYPE
			SYNTAX	INTEGER
			MAX-ACCESS	read-only
			STATUS	current
			::= { hmWanMbusE9 44 }

hmWanMbusE9Value13		OBJECT-TYPE
			SYNTAX	INTEGER
			MAX-ACCESS	read-only
			STATUS	current
			::= { hmWanMbusE9 45 }

hmWanMbusE9VIF14		OBJECT-TYPE
			SYNTAX	INTEGER
			MAX-ACCESS	read-only
			STATUS	current
			::= { hmWanMbusE9 46 }

hmWanMbusE9Value14		OBJECT-TYPE
			SYNTAX	INTEGER
			MAX-ACCESS	read-only
			STATUS	current
			::= { hmWanMbusE9 47 }

hmWanMbusE9VIF15		OBJECT-TYPE
			SYNTAX	INTEGER
			MAX-ACCESS	read-only
			STATUS	current
			::= { hmWanMbusE9 48 }

hmWanMbusE9Value15		OBJECT-TYPE
			SYNTAX	INTEGER
			MAX-ACCESS	read-only
			STATUS	current
			::= { hmWanMbusE9 49 }

hmWanMbusE9VIF16		OBJECT-TYPE
			SYNTAX	INTEGER
			MAX-ACCESS	read-only
			STATUS	current
			::= { hmWanMbusE9 50 }

hmWanMbusE9Value16		OBJECT-TYPE
			SYNTAX	INTEGER
			MAX-ACCESS	read-only
			STATUS	current
			::= { hmWanMbusE9 51 }

hmWanMbusE9VIF17		OBJECT-TYPE
			SYNTAX	INTEGER
			MAX-ACCESS	read-only
			STATUS	current
			::= { hmWanMbusE9 52 }

hmWanMbusE9Value17		OBJECT-TYPE
			SYNTAX	INTEGER
			MAX-ACCESS	read-only
			STATUS	current
			::= { hmWanMbusE9 53 }

hmWanMbusE9VIF18		OBJECT-TYPE
			SYNTAX	INTEGER
			MAX-ACCESS	read-only
			STATUS	current
			::= { hmWanMbusE9 54 }

hmWanMbusE9Value18		OBJECT-TYPE
			SYNTAX	INTEGER
			MAX-ACCESS	read-only
			STATUS	current
			::= { hmWanMbusE9 55 }

hmWanMbusE9VIF19		OBJECT-TYPE
			SYNTAX	INTEGER
			MAX-ACCESS	read-only
			STATUS	current
			::= { hmWanMbusE9 56 }

hmWanMbusE9Value19		OBJECT-TYPE
			SYNTAX	INTEGER
			MAX-ACCESS	read-only
			STATUS	current
			::= { hmWanMbusE9 57 }

hmWanMbusE9VIF1A		OBJECT-TYPE
			SYNTAX	INTEGER
			MAX-ACCESS	read-only
			STATUS	current
			::= { hmWanMbusE9 58 }

hmWanMbusE9Value1A		OBJECT-TYPE
			SYNTAX	INTEGER
			MAX-ACCESS	read-only
			STATUS	current
			::= { hmWanMbusE9 59 }

hmWanMbusE9VIF1B		OBJECT-TYPE
			SYNTAX	INTEGER
			MAX-ACCESS	read-only
			STATUS	current
			::= { hmWanMbusE9 60 }

hmWanMbusE9Value1B		OBJECT-TYPE
			SYNTAX	INTEGER
			MAX-ACCESS	read-only
			STATUS	current
			::= { hmWanMbusE9 61 }

hmWanMbusE9VIF1C		OBJECT-TYPE
			SYNTAX	INTEGER
			MAX-ACCESS	read-only
			STATUS	current
			::= { hmWanMbusE9 62 }

hmWanMbusE9Value1C		OBJECT-TYPE
			SYNTAX	INTEGER
			MAX-ACCESS	read-only
			STATUS	current
			::= { hmWanMbusE9 63 }

hmWanMbusE9VIF1D		OBJECT-TYPE
			SYNTAX	INTEGER
			MAX-ACCESS	read-only
			STATUS	current
			::= { hmWanMbusE9 64 }

hmWanMbusE9Value1D		OBJECT-TYPE
			SYNTAX	INTEGER
			MAX-ACCESS	read-only
			STATUS	current
			::= { hmWanMbusE9 65 }

hmWanMbusE9VIF1E		OBJECT-TYPE
			SYNTAX	INTEGER
			MAX-ACCESS	read-only
			STATUS	current
			::= { hmWanMbusE9 66 }

hmWanMbusE9Value1E		OBJECT-TYPE
			SYNTAX	INTEGER
			MAX-ACCESS	read-only
			STATUS	current
			::= { hmWanMbusE9 67 }

hmWanMbusE9VIF1F		OBJECT-TYPE
			SYNTAX	INTEGER
			MAX-ACCESS	read-only
			STATUS	current
			::= { hmWanMbusE9 68 }

hmWanMbusE9Value1F		OBJECT-TYPE
			SYNTAX	INTEGER
			MAX-ACCESS	read-only
			STATUS	current
			::= { hmWanMbusE9 69 }

hmWanMbusE9VIF20		OBJECT-TYPE
			SYNTAX	INTEGER
			MAX-ACCESS	read-only
			STATUS	current
			::= { hmWanMbusE9 70 }

hmWanMbusE9Value20		OBJECT-TYPE
			SYNTAX	INTEGER
			MAX-ACCESS	read-only
			STATUS	current
			::= { hmWanMbusE9 71 }

hmWanMbusE9VIF21		OBJECT-TYPE
			SYNTAX	INTEGER
			MAX-ACCESS	read-only
			STATUS	current
			::= { hmWanMbusE9 72 }

hmWanMbusE9Value21		OBJECT-TYPE
			SYNTAX	INTEGER
			MAX-ACCESS	read-only
			STATUS	current
			::= { hmWanMbusE9 73 }

hmWanMbusE9VIF22		OBJECT-TYPE
			SYNTAX	INTEGER
			MAX-ACCESS	read-only
			STATUS	current
			::= { hmWanMbusE9 74 }

hmWanMbusE9Value22		OBJECT-TYPE
			SYNTAX	INTEGER
			MAX-ACCESS	read-only
			STATUS	current
			::= { hmWanMbusE9 75 }

hmWanMbusE9VIF23		OBJECT-TYPE
			SYNTAX	INTEGER
			MAX-ACCESS	read-only
			STATUS	current
			::= { hmWanMbusE9 76 }

hmWanMbusE9Value23		OBJECT-TYPE
			SYNTAX	INTEGER
			MAX-ACCESS	read-only
			STATUS	current
			::= { hmWanMbusE9 77 }

hmWanMbusE9VIF24		OBJECT-TYPE
			SYNTAX	INTEGER
			MAX-ACCESS	read-only
			STATUS	current
			::= { hmWanMbusE9 78 }

hmWanMbusE9Value24		OBJECT-TYPE
			SYNTAX	INTEGER
			MAX-ACCESS	read-only
			STATUS	current
			::= { hmWanMbusE9 79 }

hmWanMbusE9VIF25		OBJECT-TYPE
			SYNTAX	INTEGER
			MAX-ACCESS	read-only
			STATUS	current
			::= { hmWanMbusE9 80 }

hmWanMbusE9Value25		OBJECT-TYPE
			SYNTAX	INTEGER
			MAX-ACCESS	read-only
			STATUS	current
			::= { hmWanMbusE9 81 }

hmWanMbusE9VIF26		OBJECT-TYPE
			SYNTAX	INTEGER
			MAX-ACCESS	read-only
			STATUS	current
			::= { hmWanMbusE9 82 }

hmWanMbusE9Value26		OBJECT-TYPE
			SYNTAX	INTEGER
			MAX-ACCESS	read-only
			STATUS	current
			::= { hmWanMbusE9 83 }

hmWanMbusE9VIF27		OBJECT-TYPE
			SYNTAX	INTEGER
			MAX-ACCESS	read-only
			STATUS	current
			::= { hmWanMbusE9 84 }

hmWanMbusE9Value27		OBJECT-TYPE
			SYNTAX	INTEGER
			MAX-ACCESS	read-only
			STATUS	current
			::= { hmWanMbusE9 85 }

hmWanMbusE9VIF28		OBJECT-TYPE
			SYNTAX	INTEGER
			MAX-ACCESS	read-only
			STATUS	current
			::= { hmWanMbusE9 86 }

hmWanMbusE9Value28		OBJECT-TYPE
			SYNTAX	INTEGER
			MAX-ACCESS	read-only
			STATUS	current
			::= { hmWanMbusE9 87 }

hmWanMbusE9VIF29		OBJECT-TYPE
			SYNTAX	INTEGER
			MAX-ACCESS	read-only
			STATUS	current
			::= { hmWanMbusE9 88 }

hmWanMbusE9Value29		OBJECT-TYPE
			SYNTAX	INTEGER
			MAX-ACCESS	read-only
			STATUS	current
			::= { hmWanMbusE9 89 }

hmWanMbusE9VIF2A		OBJECT-TYPE
			SYNTAX	INTEGER
			MAX-ACCESS	read-only
			STATUS	current
			::= { hmWanMbusE9 90 }

hmWanMbusE9Value2A		OBJECT-TYPE
			SYNTAX	INTEGER
			MAX-ACCESS	read-only
			STATUS	current
			::= { hmWanMbusE9 91 }

hmWanMbusE9VIF2B		OBJECT-TYPE
			SYNTAX	INTEGER
			MAX-ACCESS	read-only
			STATUS	current
			::= { hmWanMbusE9 92 }

hmWanMbusE9Value2B		OBJECT-TYPE
			SYNTAX	INTEGER
			MAX-ACCESS	read-only
			STATUS	current
			::= { hmWanMbusE9 93 }

hmWanMbusE9VIF2C		OBJECT-TYPE
			SYNTAX	INTEGER
			MAX-ACCESS	read-only
			STATUS	current
			::= { hmWanMbusE9 94 }

hmWanMbusE9Value2C		OBJECT-TYPE
			SYNTAX	INTEGER
			MAX-ACCESS	read-only
			STATUS	current
			::= { hmWanMbusE9 95 }

hmWanMbusE9VIF2D		OBJECT-TYPE
			SYNTAX	INTEGER
			MAX-ACCESS	read-only
			STATUS	current
			::= { hmWanMbusE9 96 }

hmWanMbusE9Value2D		OBJECT-TYPE
			SYNTAX	INTEGER
			MAX-ACCESS	read-only
			STATUS	current
			::= { hmWanMbusE9 97 }

hmWanMbusE9VIF2E		OBJECT-TYPE
			SYNTAX	INTEGER
			MAX-ACCESS	read-only
			STATUS	current
			::= { hmWanMbusE9 98 }

hmWanMbusE9Value2E		OBJECT-TYPE
			SYNTAX	INTEGER
			MAX-ACCESS	read-only
			STATUS	current
			::= { hmWanMbusE9 99 }

hmWanMbusE9VIF2F		OBJECT-TYPE
			SYNTAX	INTEGER
			MAX-ACCESS	read-only
			STATUS	current
			::= { hmWanMbusE9 100 }

hmWanMbusE9Value2F		OBJECT-TYPE
			SYNTAX	INTEGER
			MAX-ACCESS	read-only
			STATUS	current
			::= { hmWanMbusE9 101 }

hmWanMbusEA			OBJECT IDENTIFIER ::= { hmWanMbus 234 }

hmWanMbusEAIdNumber		OBJECT-TYPE
			SYNTAX	Gauge32
			MAX-ACCESS	read-only
			STATUS	current
			::= { hmWanMbusEA 1 }

hmWanMbusEAManufacturer	OBJECT-TYPE
			SYNTAX	Gauge32
			MAX-ACCESS	read-only
			STATUS	current
			::= { hmWanMbusEA 2 }

hmWanMbusEAVersion		OBJECT-TYPE
			SYNTAX	Gauge32
			MAX-ACCESS	read-only
			STATUS	current
			::= { hmWanMbusEA 3 }

hmWanMbusEAMedium		OBJECT-TYPE
			SYNTAX	Gauge32
			MAX-ACCESS	read-only
			STATUS	current
			::= { hmWanMbusEA 4 }

hmWanMbusEAStatus		OBJECT-TYPE
			SYNTAX	Gauge32
			MAX-ACCESS	read-only
			STATUS	current
			::= { hmWanMbusEA 5 }

hmWanMbusEAVIF00		OBJECT-TYPE
			SYNTAX	INTEGER
			MAX-ACCESS	read-only
			STATUS	current
			::= { hmWanMbusEA 6 }

hmWanMbusEAValue00		OBJECT-TYPE
			SYNTAX	INTEGER
			MAX-ACCESS	read-only
			STATUS	current
			::= { hmWanMbusEA 7 }

hmWanMbusEAVIF01		OBJECT-TYPE
			SYNTAX	INTEGER
			MAX-ACCESS	read-only
			STATUS	current
			::= { hmWanMbusEA 8 }

hmWanMbusEAValue01		OBJECT-TYPE
			SYNTAX	INTEGER
			MAX-ACCESS	read-only
			STATUS	current
			::= { hmWanMbusEA 9 }

hmWanMbusEAVIF02		OBJECT-TYPE
			SYNTAX	INTEGER
			MAX-ACCESS	read-only
			STATUS	current
			::= { hmWanMbusEA 10 }

hmWanMbusEAValue02		OBJECT-TYPE
			SYNTAX	INTEGER
			MAX-ACCESS	read-only
			STATUS	current
			::= { hmWanMbusEA 11 }

hmWanMbusEAVIF03		OBJECT-TYPE
			SYNTAX	INTEGER
			MAX-ACCESS	read-only
			STATUS	current
			::= { hmWanMbusEA 12 }

hmWanMbusEAValue03		OBJECT-TYPE
			SYNTAX	INTEGER
			MAX-ACCESS	read-only
			STATUS	current
			::= { hmWanMbusEA 13 }

hmWanMbusEAVIF04		OBJECT-TYPE
			SYNTAX	INTEGER
			MAX-ACCESS	read-only
			STATUS	current
			::= { hmWanMbusEA 14 }

hmWanMbusEAValue04		OBJECT-TYPE
			SYNTAX	INTEGER
			MAX-ACCESS	read-only
			STATUS	current
			::= { hmWanMbusEA 15 }

hmWanMbusEAVIF05		OBJECT-TYPE
			SYNTAX	INTEGER
			MAX-ACCESS	read-only
			STATUS	current
			::= { hmWanMbusEA 16 }

hmWanMbusEAValue05		OBJECT-TYPE
			SYNTAX	INTEGER
			MAX-ACCESS	read-only
			STATUS	current
			::= { hmWanMbusEA 17 }

hmWanMbusEAVIF06		OBJECT-TYPE
			SYNTAX	INTEGER
			MAX-ACCESS	read-only
			STATUS	current
			::= { hmWanMbusEA 18 }

hmWanMbusEAValue06		OBJECT-TYPE
			SYNTAX	INTEGER
			MAX-ACCESS	read-only
			STATUS	current
			::= { hmWanMbusEA 19 }

hmWanMbusEAVIF07		OBJECT-TYPE
			SYNTAX	INTEGER
			MAX-ACCESS	read-only
			STATUS	current
			::= { hmWanMbusEA 20 }

hmWanMbusEAValue07		OBJECT-TYPE
			SYNTAX	INTEGER
			MAX-ACCESS	read-only
			STATUS	current
			::= { hmWanMbusEA 21 }

hmWanMbusEAVIF08		OBJECT-TYPE
			SYNTAX	INTEGER
			MAX-ACCESS	read-only
			STATUS	current
			::= { hmWanMbusEA 22 }

hmWanMbusEAValue08		OBJECT-TYPE
			SYNTAX	INTEGER
			MAX-ACCESS	read-only
			STATUS	current
			::= { hmWanMbusEA 23 }

hmWanMbusEAVIF09		OBJECT-TYPE
			SYNTAX	INTEGER
			MAX-ACCESS	read-only
			STATUS	current
			::= { hmWanMbusEA 24 }

hmWanMbusEAValue09		OBJECT-TYPE
			SYNTAX	INTEGER
			MAX-ACCESS	read-only
			STATUS	current
			::= { hmWanMbusEA 25 }

hmWanMbusEAVIF0A		OBJECT-TYPE
			SYNTAX	INTEGER
			MAX-ACCESS	read-only
			STATUS	current
			::= { hmWanMbusEA 26 }

hmWanMbusEAValue0A		OBJECT-TYPE
			SYNTAX	INTEGER
			MAX-ACCESS	read-only
			STATUS	current
			::= { hmWanMbusEA 27 }

hmWanMbusEAVIF0B		OBJECT-TYPE
			SYNTAX	INTEGER
			MAX-ACCESS	read-only
			STATUS	current
			::= { hmWanMbusEA 28 }

hmWanMbusEAValue0B		OBJECT-TYPE
			SYNTAX	INTEGER
			MAX-ACCESS	read-only
			STATUS	current
			::= { hmWanMbusEA 29 }

hmWanMbusEAVIF0C		OBJECT-TYPE
			SYNTAX	INTEGER
			MAX-ACCESS	read-only
			STATUS	current
			::= { hmWanMbusEA 30 }

hmWanMbusEAValue0C		OBJECT-TYPE
			SYNTAX	INTEGER
			MAX-ACCESS	read-only
			STATUS	current
			::= { hmWanMbusEA 31 }

hmWanMbusEAVIF0D		OBJECT-TYPE
			SYNTAX	INTEGER
			MAX-ACCESS	read-only
			STATUS	current
			::= { hmWanMbusEA 32 }

hmWanMbusEAValue0D		OBJECT-TYPE
			SYNTAX	INTEGER
			MAX-ACCESS	read-only
			STATUS	current
			::= { hmWanMbusEA 33 }

hmWanMbusEAVIF0E		OBJECT-TYPE
			SYNTAX	INTEGER
			MAX-ACCESS	read-only
			STATUS	current
			::= { hmWanMbusEA 34 }

hmWanMbusEAValue0E		OBJECT-TYPE
			SYNTAX	INTEGER
			MAX-ACCESS	read-only
			STATUS	current
			::= { hmWanMbusEA 35 }

hmWanMbusEAVIF0F		OBJECT-TYPE
			SYNTAX	INTEGER
			MAX-ACCESS	read-only
			STATUS	current
			::= { hmWanMbusEA 36 }

hmWanMbusEAValue0F		OBJECT-TYPE
			SYNTAX	INTEGER
			MAX-ACCESS	read-only
			STATUS	current
			::= { hmWanMbusEA 37 }

hmWanMbusEAVIF10		OBJECT-TYPE
			SYNTAX	INTEGER
			MAX-ACCESS	read-only
			STATUS	current
			::= { hmWanMbusEA 38 }

hmWanMbusEAValue10		OBJECT-TYPE
			SYNTAX	INTEGER
			MAX-ACCESS	read-only
			STATUS	current
			::= { hmWanMbusEA 39 }

hmWanMbusEAVIF11		OBJECT-TYPE
			SYNTAX	INTEGER
			MAX-ACCESS	read-only
			STATUS	current
			::= { hmWanMbusEA 40 }

hmWanMbusEAValue11		OBJECT-TYPE
			SYNTAX	INTEGER
			MAX-ACCESS	read-only
			STATUS	current
			::= { hmWanMbusEA 41 }

hmWanMbusEAVIF12		OBJECT-TYPE
			SYNTAX	INTEGER
			MAX-ACCESS	read-only
			STATUS	current
			::= { hmWanMbusEA 42 }

hmWanMbusEAValue12		OBJECT-TYPE
			SYNTAX	INTEGER
			MAX-ACCESS	read-only
			STATUS	current
			::= { hmWanMbusEA 43 }

hmWanMbusEAVIF13		OBJECT-TYPE
			SYNTAX	INTEGER
			MAX-ACCESS	read-only
			STATUS	current
			::= { hmWanMbusEA 44 }

hmWanMbusEAValue13		OBJECT-TYPE
			SYNTAX	INTEGER
			MAX-ACCESS	read-only
			STATUS	current
			::= { hmWanMbusEA 45 }

hmWanMbusEAVIF14		OBJECT-TYPE
			SYNTAX	INTEGER
			MAX-ACCESS	read-only
			STATUS	current
			::= { hmWanMbusEA 46 }

hmWanMbusEAValue14		OBJECT-TYPE
			SYNTAX	INTEGER
			MAX-ACCESS	read-only
			STATUS	current
			::= { hmWanMbusEA 47 }

hmWanMbusEAVIF15		OBJECT-TYPE
			SYNTAX	INTEGER
			MAX-ACCESS	read-only
			STATUS	current
			::= { hmWanMbusEA 48 }

hmWanMbusEAValue15		OBJECT-TYPE
			SYNTAX	INTEGER
			MAX-ACCESS	read-only
			STATUS	current
			::= { hmWanMbusEA 49 }

hmWanMbusEAVIF16		OBJECT-TYPE
			SYNTAX	INTEGER
			MAX-ACCESS	read-only
			STATUS	current
			::= { hmWanMbusEA 50 }

hmWanMbusEAValue16		OBJECT-TYPE
			SYNTAX	INTEGER
			MAX-ACCESS	read-only
			STATUS	current
			::= { hmWanMbusEA 51 }

hmWanMbusEAVIF17		OBJECT-TYPE
			SYNTAX	INTEGER
			MAX-ACCESS	read-only
			STATUS	current
			::= { hmWanMbusEA 52 }

hmWanMbusEAValue17		OBJECT-TYPE
			SYNTAX	INTEGER
			MAX-ACCESS	read-only
			STATUS	current
			::= { hmWanMbusEA 53 }

hmWanMbusEAVIF18		OBJECT-TYPE
			SYNTAX	INTEGER
			MAX-ACCESS	read-only
			STATUS	current
			::= { hmWanMbusEA 54 }

hmWanMbusEAValue18		OBJECT-TYPE
			SYNTAX	INTEGER
			MAX-ACCESS	read-only
			STATUS	current
			::= { hmWanMbusEA 55 }

hmWanMbusEAVIF19		OBJECT-TYPE
			SYNTAX	INTEGER
			MAX-ACCESS	read-only
			STATUS	current
			::= { hmWanMbusEA 56 }

hmWanMbusEAValue19		OBJECT-TYPE
			SYNTAX	INTEGER
			MAX-ACCESS	read-only
			STATUS	current
			::= { hmWanMbusEA 57 }

hmWanMbusEAVIF1A		OBJECT-TYPE
			SYNTAX	INTEGER
			MAX-ACCESS	read-only
			STATUS	current
			::= { hmWanMbusEA 58 }

hmWanMbusEAValue1A		OBJECT-TYPE
			SYNTAX	INTEGER
			MAX-ACCESS	read-only
			STATUS	current
			::= { hmWanMbusEA 59 }

hmWanMbusEAVIF1B		OBJECT-TYPE
			SYNTAX	INTEGER
			MAX-ACCESS	read-only
			STATUS	current
			::= { hmWanMbusEA 60 }

hmWanMbusEAValue1B		OBJECT-TYPE
			SYNTAX	INTEGER
			MAX-ACCESS	read-only
			STATUS	current
			::= { hmWanMbusEA 61 }

hmWanMbusEAVIF1C		OBJECT-TYPE
			SYNTAX	INTEGER
			MAX-ACCESS	read-only
			STATUS	current
			::= { hmWanMbusEA 62 }

hmWanMbusEAValue1C		OBJECT-TYPE
			SYNTAX	INTEGER
			MAX-ACCESS	read-only
			STATUS	current
			::= { hmWanMbusEA 63 }

hmWanMbusEAVIF1D		OBJECT-TYPE
			SYNTAX	INTEGER
			MAX-ACCESS	read-only
			STATUS	current
			::= { hmWanMbusEA 64 }

hmWanMbusEAValue1D		OBJECT-TYPE
			SYNTAX	INTEGER
			MAX-ACCESS	read-only
			STATUS	current
			::= { hmWanMbusEA 65 }

hmWanMbusEAVIF1E		OBJECT-TYPE
			SYNTAX	INTEGER
			MAX-ACCESS	read-only
			STATUS	current
			::= { hmWanMbusEA 66 }

hmWanMbusEAValue1E		OBJECT-TYPE
			SYNTAX	INTEGER
			MAX-ACCESS	read-only
			STATUS	current
			::= { hmWanMbusEA 67 }

hmWanMbusEAVIF1F		OBJECT-TYPE
			SYNTAX	INTEGER
			MAX-ACCESS	read-only
			STATUS	current
			::= { hmWanMbusEA 68 }

hmWanMbusEAValue1F		OBJECT-TYPE
			SYNTAX	INTEGER
			MAX-ACCESS	read-only
			STATUS	current
			::= { hmWanMbusEA 69 }

hmWanMbusEAVIF20		OBJECT-TYPE
			SYNTAX	INTEGER
			MAX-ACCESS	read-only
			STATUS	current
			::= { hmWanMbusEA 70 }

hmWanMbusEAValue20		OBJECT-TYPE
			SYNTAX	INTEGER
			MAX-ACCESS	read-only
			STATUS	current
			::= { hmWanMbusEA 71 }

hmWanMbusEAVIF21		OBJECT-TYPE
			SYNTAX	INTEGER
			MAX-ACCESS	read-only
			STATUS	current
			::= { hmWanMbusEA 72 }

hmWanMbusEAValue21		OBJECT-TYPE
			SYNTAX	INTEGER
			MAX-ACCESS	read-only
			STATUS	current
			::= { hmWanMbusEA 73 }

hmWanMbusEAVIF22		OBJECT-TYPE
			SYNTAX	INTEGER
			MAX-ACCESS	read-only
			STATUS	current
			::= { hmWanMbusEA 74 }

hmWanMbusEAValue22		OBJECT-TYPE
			SYNTAX	INTEGER
			MAX-ACCESS	read-only
			STATUS	current
			::= { hmWanMbusEA 75 }

hmWanMbusEAVIF23		OBJECT-TYPE
			SYNTAX	INTEGER
			MAX-ACCESS	read-only
			STATUS	current
			::= { hmWanMbusEA 76 }

hmWanMbusEAValue23		OBJECT-TYPE
			SYNTAX	INTEGER
			MAX-ACCESS	read-only
			STATUS	current
			::= { hmWanMbusEA 77 }

hmWanMbusEAVIF24		OBJECT-TYPE
			SYNTAX	INTEGER
			MAX-ACCESS	read-only
			STATUS	current
			::= { hmWanMbusEA 78 }

hmWanMbusEAValue24		OBJECT-TYPE
			SYNTAX	INTEGER
			MAX-ACCESS	read-only
			STATUS	current
			::= { hmWanMbusEA 79 }

hmWanMbusEAVIF25		OBJECT-TYPE
			SYNTAX	INTEGER
			MAX-ACCESS	read-only
			STATUS	current
			::= { hmWanMbusEA 80 }

hmWanMbusEAValue25		OBJECT-TYPE
			SYNTAX	INTEGER
			MAX-ACCESS	read-only
			STATUS	current
			::= { hmWanMbusEA 81 }

hmWanMbusEAVIF26		OBJECT-TYPE
			SYNTAX	INTEGER
			MAX-ACCESS	read-only
			STATUS	current
			::= { hmWanMbusEA 82 }

hmWanMbusEAValue26		OBJECT-TYPE
			SYNTAX	INTEGER
			MAX-ACCESS	read-only
			STATUS	current
			::= { hmWanMbusEA 83 }

hmWanMbusEAVIF27		OBJECT-TYPE
			SYNTAX	INTEGER
			MAX-ACCESS	read-only
			STATUS	current
			::= { hmWanMbusEA 84 }

hmWanMbusEAValue27		OBJECT-TYPE
			SYNTAX	INTEGER
			MAX-ACCESS	read-only
			STATUS	current
			::= { hmWanMbusEA 85 }

hmWanMbusEAVIF28		OBJECT-TYPE
			SYNTAX	INTEGER
			MAX-ACCESS	read-only
			STATUS	current
			::= { hmWanMbusEA 86 }

hmWanMbusEAValue28		OBJECT-TYPE
			SYNTAX	INTEGER
			MAX-ACCESS	read-only
			STATUS	current
			::= { hmWanMbusEA 87 }

hmWanMbusEAVIF29		OBJECT-TYPE
			SYNTAX	INTEGER
			MAX-ACCESS	read-only
			STATUS	current
			::= { hmWanMbusEA 88 }

hmWanMbusEAValue29		OBJECT-TYPE
			SYNTAX	INTEGER
			MAX-ACCESS	read-only
			STATUS	current
			::= { hmWanMbusEA 89 }

hmWanMbusEAVIF2A		OBJECT-TYPE
			SYNTAX	INTEGER
			MAX-ACCESS	read-only
			STATUS	current
			::= { hmWanMbusEA 90 }

hmWanMbusEAValue2A		OBJECT-TYPE
			SYNTAX	INTEGER
			MAX-ACCESS	read-only
			STATUS	current
			::= { hmWanMbusEA 91 }

hmWanMbusEAVIF2B		OBJECT-TYPE
			SYNTAX	INTEGER
			MAX-ACCESS	read-only
			STATUS	current
			::= { hmWanMbusEA 92 }

hmWanMbusEAValue2B		OBJECT-TYPE
			SYNTAX	INTEGER
			MAX-ACCESS	read-only
			STATUS	current
			::= { hmWanMbusEA 93 }

hmWanMbusEAVIF2C		OBJECT-TYPE
			SYNTAX	INTEGER
			MAX-ACCESS	read-only
			STATUS	current
			::= { hmWanMbusEA 94 }

hmWanMbusEAValue2C		OBJECT-TYPE
			SYNTAX	INTEGER
			MAX-ACCESS	read-only
			STATUS	current
			::= { hmWanMbusEA 95 }

hmWanMbusEAVIF2D		OBJECT-TYPE
			SYNTAX	INTEGER
			MAX-ACCESS	read-only
			STATUS	current
			::= { hmWanMbusEA 96 }

hmWanMbusEAValue2D		OBJECT-TYPE
			SYNTAX	INTEGER
			MAX-ACCESS	read-only
			STATUS	current
			::= { hmWanMbusEA 97 }

hmWanMbusEAVIF2E		OBJECT-TYPE
			SYNTAX	INTEGER
			MAX-ACCESS	read-only
			STATUS	current
			::= { hmWanMbusEA 98 }

hmWanMbusEAValue2E		OBJECT-TYPE
			SYNTAX	INTEGER
			MAX-ACCESS	read-only
			STATUS	current
			::= { hmWanMbusEA 99 }

hmWanMbusEAVIF2F		OBJECT-TYPE
			SYNTAX	INTEGER
			MAX-ACCESS	read-only
			STATUS	current
			::= { hmWanMbusEA 100 }

hmWanMbusEAValue2F		OBJECT-TYPE
			SYNTAX	INTEGER
			MAX-ACCESS	read-only
			STATUS	current
			::= { hmWanMbusEA 101 }

hmWanMbusEB			OBJECT IDENTIFIER ::= { hmWanMbus 235 }

hmWanMbusEBIdNumber		OBJECT-TYPE
			SYNTAX	Gauge32
			MAX-ACCESS	read-only
			STATUS	current
			::= { hmWanMbusEB 1 }

hmWanMbusEBManufacturer	OBJECT-TYPE
			SYNTAX	Gauge32
			MAX-ACCESS	read-only
			STATUS	current
			::= { hmWanMbusEB 2 }

hmWanMbusEBVersion		OBJECT-TYPE
			SYNTAX	Gauge32
			MAX-ACCESS	read-only
			STATUS	current
			::= { hmWanMbusEB 3 }

hmWanMbusEBMedium		OBJECT-TYPE
			SYNTAX	Gauge32
			MAX-ACCESS	read-only
			STATUS	current
			::= { hmWanMbusEB 4 }

hmWanMbusEBStatus		OBJECT-TYPE
			SYNTAX	Gauge32
			MAX-ACCESS	read-only
			STATUS	current
			::= { hmWanMbusEB 5 }

hmWanMbusEBVIF00		OBJECT-TYPE
			SYNTAX	INTEGER
			MAX-ACCESS	read-only
			STATUS	current
			::= { hmWanMbusEB 6 }

hmWanMbusEBValue00		OBJECT-TYPE
			SYNTAX	INTEGER
			MAX-ACCESS	read-only
			STATUS	current
			::= { hmWanMbusEB 7 }

hmWanMbusEBVIF01		OBJECT-TYPE
			SYNTAX	INTEGER
			MAX-ACCESS	read-only
			STATUS	current
			::= { hmWanMbusEB 8 }

hmWanMbusEBValue01		OBJECT-TYPE
			SYNTAX	INTEGER
			MAX-ACCESS	read-only
			STATUS	current
			::= { hmWanMbusEB 9 }

hmWanMbusEBVIF02		OBJECT-TYPE
			SYNTAX	INTEGER
			MAX-ACCESS	read-only
			STATUS	current
			::= { hmWanMbusEB 10 }

hmWanMbusEBValue02		OBJECT-TYPE
			SYNTAX	INTEGER
			MAX-ACCESS	read-only
			STATUS	current
			::= { hmWanMbusEB 11 }

hmWanMbusEBVIF03		OBJECT-TYPE
			SYNTAX	INTEGER
			MAX-ACCESS	read-only
			STATUS	current
			::= { hmWanMbusEB 12 }

hmWanMbusEBValue03		OBJECT-TYPE
			SYNTAX	INTEGER
			MAX-ACCESS	read-only
			STATUS	current
			::= { hmWanMbusEB 13 }

hmWanMbusEBVIF04		OBJECT-TYPE
			SYNTAX	INTEGER
			MAX-ACCESS	read-only
			STATUS	current
			::= { hmWanMbusEB 14 }

hmWanMbusEBValue04		OBJECT-TYPE
			SYNTAX	INTEGER
			MAX-ACCESS	read-only
			STATUS	current
			::= { hmWanMbusEB 15 }

hmWanMbusEBVIF05		OBJECT-TYPE
			SYNTAX	INTEGER
			MAX-ACCESS	read-only
			STATUS	current
			::= { hmWanMbusEB 16 }

hmWanMbusEBValue05		OBJECT-TYPE
			SYNTAX	INTEGER
			MAX-ACCESS	read-only
			STATUS	current
			::= { hmWanMbusEB 17 }

hmWanMbusEBVIF06		OBJECT-TYPE
			SYNTAX	INTEGER
			MAX-ACCESS	read-only
			STATUS	current
			::= { hmWanMbusEB 18 }

hmWanMbusEBValue06		OBJECT-TYPE
			SYNTAX	INTEGER
			MAX-ACCESS	read-only
			STATUS	current
			::= { hmWanMbusEB 19 }

hmWanMbusEBVIF07		OBJECT-TYPE
			SYNTAX	INTEGER
			MAX-ACCESS	read-only
			STATUS	current
			::= { hmWanMbusEB 20 }

hmWanMbusEBValue07		OBJECT-TYPE
			SYNTAX	INTEGER
			MAX-ACCESS	read-only
			STATUS	current
			::= { hmWanMbusEB 21 }

hmWanMbusEBVIF08		OBJECT-TYPE
			SYNTAX	INTEGER
			MAX-ACCESS	read-only
			STATUS	current
			::= { hmWanMbusEB 22 }

hmWanMbusEBValue08		OBJECT-TYPE
			SYNTAX	INTEGER
			MAX-ACCESS	read-only
			STATUS	current
			::= { hmWanMbusEB 23 }

hmWanMbusEBVIF09		OBJECT-TYPE
			SYNTAX	INTEGER
			MAX-ACCESS	read-only
			STATUS	current
			::= { hmWanMbusEB 24 }

hmWanMbusEBValue09		OBJECT-TYPE
			SYNTAX	INTEGER
			MAX-ACCESS	read-only
			STATUS	current
			::= { hmWanMbusEB 25 }

hmWanMbusEBVIF0A		OBJECT-TYPE
			SYNTAX	INTEGER
			MAX-ACCESS	read-only
			STATUS	current
			::= { hmWanMbusEB 26 }

hmWanMbusEBValue0A		OBJECT-TYPE
			SYNTAX	INTEGER
			MAX-ACCESS	read-only
			STATUS	current
			::= { hmWanMbusEB 27 }

hmWanMbusEBVIF0B		OBJECT-TYPE
			SYNTAX	INTEGER
			MAX-ACCESS	read-only
			STATUS	current
			::= { hmWanMbusEB 28 }

hmWanMbusEBValue0B		OBJECT-TYPE
			SYNTAX	INTEGER
			MAX-ACCESS	read-only
			STATUS	current
			::= { hmWanMbusEB 29 }

hmWanMbusEBVIF0C		OBJECT-TYPE
			SYNTAX	INTEGER
			MAX-ACCESS	read-only
			STATUS	current
			::= { hmWanMbusEB 30 }

hmWanMbusEBValue0C		OBJECT-TYPE
			SYNTAX	INTEGER
			MAX-ACCESS	read-only
			STATUS	current
			::= { hmWanMbusEB 31 }

hmWanMbusEBVIF0D		OBJECT-TYPE
			SYNTAX	INTEGER
			MAX-ACCESS	read-only
			STATUS	current
			::= { hmWanMbusEB 32 }

hmWanMbusEBValue0D		OBJECT-TYPE
			SYNTAX	INTEGER
			MAX-ACCESS	read-only
			STATUS	current
			::= { hmWanMbusEB 33 }

hmWanMbusEBVIF0E		OBJECT-TYPE
			SYNTAX	INTEGER
			MAX-ACCESS	read-only
			STATUS	current
			::= { hmWanMbusEB 34 }

hmWanMbusEBValue0E		OBJECT-TYPE
			SYNTAX	INTEGER
			MAX-ACCESS	read-only
			STATUS	current
			::= { hmWanMbusEB 35 }

hmWanMbusEBVIF0F		OBJECT-TYPE
			SYNTAX	INTEGER
			MAX-ACCESS	read-only
			STATUS	current
			::= { hmWanMbusEB 36 }

hmWanMbusEBValue0F		OBJECT-TYPE
			SYNTAX	INTEGER
			MAX-ACCESS	read-only
			STATUS	current
			::= { hmWanMbusEB 37 }

hmWanMbusEBVIF10		OBJECT-TYPE
			SYNTAX	INTEGER
			MAX-ACCESS	read-only
			STATUS	current
			::= { hmWanMbusEB 38 }

hmWanMbusEBValue10		OBJECT-TYPE
			SYNTAX	INTEGER
			MAX-ACCESS	read-only
			STATUS	current
			::= { hmWanMbusEB 39 }

hmWanMbusEBVIF11		OBJECT-TYPE
			SYNTAX	INTEGER
			MAX-ACCESS	read-only
			STATUS	current
			::= { hmWanMbusEB 40 }

hmWanMbusEBValue11		OBJECT-TYPE
			SYNTAX	INTEGER
			MAX-ACCESS	read-only
			STATUS	current
			::= { hmWanMbusEB 41 }

hmWanMbusEBVIF12		OBJECT-TYPE
			SYNTAX	INTEGER
			MAX-ACCESS	read-only
			STATUS	current
			::= { hmWanMbusEB 42 }

hmWanMbusEBValue12		OBJECT-TYPE
			SYNTAX	INTEGER
			MAX-ACCESS	read-only
			STATUS	current
			::= { hmWanMbusEB 43 }

hmWanMbusEBVIF13		OBJECT-TYPE
			SYNTAX	INTEGER
			MAX-ACCESS	read-only
			STATUS	current
			::= { hmWanMbusEB 44 }

hmWanMbusEBValue13		OBJECT-TYPE
			SYNTAX	INTEGER
			MAX-ACCESS	read-only
			STATUS	current
			::= { hmWanMbusEB 45 }

hmWanMbusEBVIF14		OBJECT-TYPE
			SYNTAX	INTEGER
			MAX-ACCESS	read-only
			STATUS	current
			::= { hmWanMbusEB 46 }

hmWanMbusEBValue14		OBJECT-TYPE
			SYNTAX	INTEGER
			MAX-ACCESS	read-only
			STATUS	current
			::= { hmWanMbusEB 47 }

hmWanMbusEBVIF15		OBJECT-TYPE
			SYNTAX	INTEGER
			MAX-ACCESS	read-only
			STATUS	current
			::= { hmWanMbusEB 48 }

hmWanMbusEBValue15		OBJECT-TYPE
			SYNTAX	INTEGER
			MAX-ACCESS	read-only
			STATUS	current
			::= { hmWanMbusEB 49 }

hmWanMbusEBVIF16		OBJECT-TYPE
			SYNTAX	INTEGER
			MAX-ACCESS	read-only
			STATUS	current
			::= { hmWanMbusEB 50 }

hmWanMbusEBValue16		OBJECT-TYPE
			SYNTAX	INTEGER
			MAX-ACCESS	read-only
			STATUS	current
			::= { hmWanMbusEB 51 }

hmWanMbusEBVIF17		OBJECT-TYPE
			SYNTAX	INTEGER
			MAX-ACCESS	read-only
			STATUS	current
			::= { hmWanMbusEB 52 }

hmWanMbusEBValue17		OBJECT-TYPE
			SYNTAX	INTEGER
			MAX-ACCESS	read-only
			STATUS	current
			::= { hmWanMbusEB 53 }

hmWanMbusEBVIF18		OBJECT-TYPE
			SYNTAX	INTEGER
			MAX-ACCESS	read-only
			STATUS	current
			::= { hmWanMbusEB 54 }

hmWanMbusEBValue18		OBJECT-TYPE
			SYNTAX	INTEGER
			MAX-ACCESS	read-only
			STATUS	current
			::= { hmWanMbusEB 55 }

hmWanMbusEBVIF19		OBJECT-TYPE
			SYNTAX	INTEGER
			MAX-ACCESS	read-only
			STATUS	current
			::= { hmWanMbusEB 56 }

hmWanMbusEBValue19		OBJECT-TYPE
			SYNTAX	INTEGER
			MAX-ACCESS	read-only
			STATUS	current
			::= { hmWanMbusEB 57 }

hmWanMbusEBVIF1A		OBJECT-TYPE
			SYNTAX	INTEGER
			MAX-ACCESS	read-only
			STATUS	current
			::= { hmWanMbusEB 58 }

hmWanMbusEBValue1A		OBJECT-TYPE
			SYNTAX	INTEGER
			MAX-ACCESS	read-only
			STATUS	current
			::= { hmWanMbusEB 59 }

hmWanMbusEBVIF1B		OBJECT-TYPE
			SYNTAX	INTEGER
			MAX-ACCESS	read-only
			STATUS	current
			::= { hmWanMbusEB 60 }

hmWanMbusEBValue1B		OBJECT-TYPE
			SYNTAX	INTEGER
			MAX-ACCESS	read-only
			STATUS	current
			::= { hmWanMbusEB 61 }

hmWanMbusEBVIF1C		OBJECT-TYPE
			SYNTAX	INTEGER
			MAX-ACCESS	read-only
			STATUS	current
			::= { hmWanMbusEB 62 }

hmWanMbusEBValue1C		OBJECT-TYPE
			SYNTAX	INTEGER
			MAX-ACCESS	read-only
			STATUS	current
			::= { hmWanMbusEB 63 }

hmWanMbusEBVIF1D		OBJECT-TYPE
			SYNTAX	INTEGER
			MAX-ACCESS	read-only
			STATUS	current
			::= { hmWanMbusEB 64 }

hmWanMbusEBValue1D		OBJECT-TYPE
			SYNTAX	INTEGER
			MAX-ACCESS	read-only
			STATUS	current
			::= { hmWanMbusEB 65 }

hmWanMbusEBVIF1E		OBJECT-TYPE
			SYNTAX	INTEGER
			MAX-ACCESS	read-only
			STATUS	current
			::= { hmWanMbusEB 66 }

hmWanMbusEBValue1E		OBJECT-TYPE
			SYNTAX	INTEGER
			MAX-ACCESS	read-only
			STATUS	current
			::= { hmWanMbusEB 67 }

hmWanMbusEBVIF1F		OBJECT-TYPE
			SYNTAX	INTEGER
			MAX-ACCESS	read-only
			STATUS	current
			::= { hmWanMbusEB 68 }

hmWanMbusEBValue1F		OBJECT-TYPE
			SYNTAX	INTEGER
			MAX-ACCESS	read-only
			STATUS	current
			::= { hmWanMbusEB 69 }

hmWanMbusEBVIF20		OBJECT-TYPE
			SYNTAX	INTEGER
			MAX-ACCESS	read-only
			STATUS	current
			::= { hmWanMbusEB 70 }

hmWanMbusEBValue20		OBJECT-TYPE
			SYNTAX	INTEGER
			MAX-ACCESS	read-only
			STATUS	current
			::= { hmWanMbusEB 71 }

hmWanMbusEBVIF21		OBJECT-TYPE
			SYNTAX	INTEGER
			MAX-ACCESS	read-only
			STATUS	current
			::= { hmWanMbusEB 72 }

hmWanMbusEBValue21		OBJECT-TYPE
			SYNTAX	INTEGER
			MAX-ACCESS	read-only
			STATUS	current
			::= { hmWanMbusEB 73 }

hmWanMbusEBVIF22		OBJECT-TYPE
			SYNTAX	INTEGER
			MAX-ACCESS	read-only
			STATUS	current
			::= { hmWanMbusEB 74 }

hmWanMbusEBValue22		OBJECT-TYPE
			SYNTAX	INTEGER
			MAX-ACCESS	read-only
			STATUS	current
			::= { hmWanMbusEB 75 }

hmWanMbusEBVIF23		OBJECT-TYPE
			SYNTAX	INTEGER
			MAX-ACCESS	read-only
			STATUS	current
			::= { hmWanMbusEB 76 }

hmWanMbusEBValue23		OBJECT-TYPE
			SYNTAX	INTEGER
			MAX-ACCESS	read-only
			STATUS	current
			::= { hmWanMbusEB 77 }

hmWanMbusEBVIF24		OBJECT-TYPE
			SYNTAX	INTEGER
			MAX-ACCESS	read-only
			STATUS	current
			::= { hmWanMbusEB 78 }

hmWanMbusEBValue24		OBJECT-TYPE
			SYNTAX	INTEGER
			MAX-ACCESS	read-only
			STATUS	current
			::= { hmWanMbusEB 79 }

hmWanMbusEBVIF25		OBJECT-TYPE
			SYNTAX	INTEGER
			MAX-ACCESS	read-only
			STATUS	current
			::= { hmWanMbusEB 80 }

hmWanMbusEBValue25		OBJECT-TYPE
			SYNTAX	INTEGER
			MAX-ACCESS	read-only
			STATUS	current
			::= { hmWanMbusEB 81 }

hmWanMbusEBVIF26		OBJECT-TYPE
			SYNTAX	INTEGER
			MAX-ACCESS	read-only
			STATUS	current
			::= { hmWanMbusEB 82 }

hmWanMbusEBValue26		OBJECT-TYPE
			SYNTAX	INTEGER
			MAX-ACCESS	read-only
			STATUS	current
			::= { hmWanMbusEB 83 }

hmWanMbusEBVIF27		OBJECT-TYPE
			SYNTAX	INTEGER
			MAX-ACCESS	read-only
			STATUS	current
			::= { hmWanMbusEB 84 }

hmWanMbusEBValue27		OBJECT-TYPE
			SYNTAX	INTEGER
			MAX-ACCESS	read-only
			STATUS	current
			::= { hmWanMbusEB 85 }

hmWanMbusEBVIF28		OBJECT-TYPE
			SYNTAX	INTEGER
			MAX-ACCESS	read-only
			STATUS	current
			::= { hmWanMbusEB 86 }

hmWanMbusEBValue28		OBJECT-TYPE
			SYNTAX	INTEGER
			MAX-ACCESS	read-only
			STATUS	current
			::= { hmWanMbusEB 87 }

hmWanMbusEBVIF29		OBJECT-TYPE
			SYNTAX	INTEGER
			MAX-ACCESS	read-only
			STATUS	current
			::= { hmWanMbusEB 88 }

hmWanMbusEBValue29		OBJECT-TYPE
			SYNTAX	INTEGER
			MAX-ACCESS	read-only
			STATUS	current
			::= { hmWanMbusEB 89 }

hmWanMbusEBVIF2A		OBJECT-TYPE
			SYNTAX	INTEGER
			MAX-ACCESS	read-only
			STATUS	current
			::= { hmWanMbusEB 90 }

hmWanMbusEBValue2A		OBJECT-TYPE
			SYNTAX	INTEGER
			MAX-ACCESS	read-only
			STATUS	current
			::= { hmWanMbusEB 91 }

hmWanMbusEBVIF2B		OBJECT-TYPE
			SYNTAX	INTEGER
			MAX-ACCESS	read-only
			STATUS	current
			::= { hmWanMbusEB 92 }

hmWanMbusEBValue2B		OBJECT-TYPE
			SYNTAX	INTEGER
			MAX-ACCESS	read-only
			STATUS	current
			::= { hmWanMbusEB 93 }

hmWanMbusEBVIF2C		OBJECT-TYPE
			SYNTAX	INTEGER
			MAX-ACCESS	read-only
			STATUS	current
			::= { hmWanMbusEB 94 }

hmWanMbusEBValue2C		OBJECT-TYPE
			SYNTAX	INTEGER
			MAX-ACCESS	read-only
			STATUS	current
			::= { hmWanMbusEB 95 }

hmWanMbusEBVIF2D		OBJECT-TYPE
			SYNTAX	INTEGER
			MAX-ACCESS	read-only
			STATUS	current
			::= { hmWanMbusEB 96 }

hmWanMbusEBValue2D		OBJECT-TYPE
			SYNTAX	INTEGER
			MAX-ACCESS	read-only
			STATUS	current
			::= { hmWanMbusEB 97 }

hmWanMbusEBVIF2E		OBJECT-TYPE
			SYNTAX	INTEGER
			MAX-ACCESS	read-only
			STATUS	current
			::= { hmWanMbusEB 98 }

hmWanMbusEBValue2E		OBJECT-TYPE
			SYNTAX	INTEGER
			MAX-ACCESS	read-only
			STATUS	current
			::= { hmWanMbusEB 99 }

hmWanMbusEBVIF2F		OBJECT-TYPE
			SYNTAX	INTEGER
			MAX-ACCESS	read-only
			STATUS	current
			::= { hmWanMbusEB 100 }

hmWanMbusEBValue2F		OBJECT-TYPE
			SYNTAX	INTEGER
			MAX-ACCESS	read-only
			STATUS	current
			::= { hmWanMbusEB 101 }

hmWanMbusEC			OBJECT IDENTIFIER ::= { hmWanMbus 236 }

hmWanMbusECIdNumber		OBJECT-TYPE
			SYNTAX	Gauge32
			MAX-ACCESS	read-only
			STATUS	current
			::= { hmWanMbusEC 1 }

hmWanMbusECManufacturer	OBJECT-TYPE
			SYNTAX	Gauge32
			MAX-ACCESS	read-only
			STATUS	current
			::= { hmWanMbusEC 2 }

hmWanMbusECVersion		OBJECT-TYPE
			SYNTAX	Gauge32
			MAX-ACCESS	read-only
			STATUS	current
			::= { hmWanMbusEC 3 }

hmWanMbusECMedium		OBJECT-TYPE
			SYNTAX	Gauge32
			MAX-ACCESS	read-only
			STATUS	current
			::= { hmWanMbusEC 4 }

hmWanMbusECStatus		OBJECT-TYPE
			SYNTAX	Gauge32
			MAX-ACCESS	read-only
			STATUS	current
			::= { hmWanMbusEC 5 }

hmWanMbusECVIF00		OBJECT-TYPE
			SYNTAX	INTEGER
			MAX-ACCESS	read-only
			STATUS	current
			::= { hmWanMbusEC 6 }

hmWanMbusECValue00		OBJECT-TYPE
			SYNTAX	INTEGER
			MAX-ACCESS	read-only
			STATUS	current
			::= { hmWanMbusEC 7 }

hmWanMbusECVIF01		OBJECT-TYPE
			SYNTAX	INTEGER
			MAX-ACCESS	read-only
			STATUS	current
			::= { hmWanMbusEC 8 }

hmWanMbusECValue01		OBJECT-TYPE
			SYNTAX	INTEGER
			MAX-ACCESS	read-only
			STATUS	current
			::= { hmWanMbusEC 9 }

hmWanMbusECVIF02		OBJECT-TYPE
			SYNTAX	INTEGER
			MAX-ACCESS	read-only
			STATUS	current
			::= { hmWanMbusEC 10 }

hmWanMbusECValue02		OBJECT-TYPE
			SYNTAX	INTEGER
			MAX-ACCESS	read-only
			STATUS	current
			::= { hmWanMbusEC 11 }

hmWanMbusECVIF03		OBJECT-TYPE
			SYNTAX	INTEGER
			MAX-ACCESS	read-only
			STATUS	current
			::= { hmWanMbusEC 12 }

hmWanMbusECValue03		OBJECT-TYPE
			SYNTAX	INTEGER
			MAX-ACCESS	read-only
			STATUS	current
			::= { hmWanMbusEC 13 }

hmWanMbusECVIF04		OBJECT-TYPE
			SYNTAX	INTEGER
			MAX-ACCESS	read-only
			STATUS	current
			::= { hmWanMbusEC 14 }

hmWanMbusECValue04		OBJECT-TYPE
			SYNTAX	INTEGER
			MAX-ACCESS	read-only
			STATUS	current
			::= { hmWanMbusEC 15 }

hmWanMbusECVIF05		OBJECT-TYPE
			SYNTAX	INTEGER
			MAX-ACCESS	read-only
			STATUS	current
			::= { hmWanMbusEC 16 }

hmWanMbusECValue05		OBJECT-TYPE
			SYNTAX	INTEGER
			MAX-ACCESS	read-only
			STATUS	current
			::= { hmWanMbusEC 17 }

hmWanMbusECVIF06		OBJECT-TYPE
			SYNTAX	INTEGER
			MAX-ACCESS	read-only
			STATUS	current
			::= { hmWanMbusEC 18 }

hmWanMbusECValue06		OBJECT-TYPE
			SYNTAX	INTEGER
			MAX-ACCESS	read-only
			STATUS	current
			::= { hmWanMbusEC 19 }

hmWanMbusECVIF07		OBJECT-TYPE
			SYNTAX	INTEGER
			MAX-ACCESS	read-only
			STATUS	current
			::= { hmWanMbusEC 20 }

hmWanMbusECValue07		OBJECT-TYPE
			SYNTAX	INTEGER
			MAX-ACCESS	read-only
			STATUS	current
			::= { hmWanMbusEC 21 }

hmWanMbusECVIF08		OBJECT-TYPE
			SYNTAX	INTEGER
			MAX-ACCESS	read-only
			STATUS	current
			::= { hmWanMbusEC 22 }

hmWanMbusECValue08		OBJECT-TYPE
			SYNTAX	INTEGER
			MAX-ACCESS	read-only
			STATUS	current
			::= { hmWanMbusEC 23 }

hmWanMbusECVIF09		OBJECT-TYPE
			SYNTAX	INTEGER
			MAX-ACCESS	read-only
			STATUS	current
			::= { hmWanMbusEC 24 }

hmWanMbusECValue09		OBJECT-TYPE
			SYNTAX	INTEGER
			MAX-ACCESS	read-only
			STATUS	current
			::= { hmWanMbusEC 25 }

hmWanMbusECVIF0A		OBJECT-TYPE
			SYNTAX	INTEGER
			MAX-ACCESS	read-only
			STATUS	current
			::= { hmWanMbusEC 26 }

hmWanMbusECValue0A		OBJECT-TYPE
			SYNTAX	INTEGER
			MAX-ACCESS	read-only
			STATUS	current
			::= { hmWanMbusEC 27 }

hmWanMbusECVIF0B		OBJECT-TYPE
			SYNTAX	INTEGER
			MAX-ACCESS	read-only
			STATUS	current
			::= { hmWanMbusEC 28 }

hmWanMbusECValue0B		OBJECT-TYPE
			SYNTAX	INTEGER
			MAX-ACCESS	read-only
			STATUS	current
			::= { hmWanMbusEC 29 }

hmWanMbusECVIF0C		OBJECT-TYPE
			SYNTAX	INTEGER
			MAX-ACCESS	read-only
			STATUS	current
			::= { hmWanMbusEC 30 }

hmWanMbusECValue0C		OBJECT-TYPE
			SYNTAX	INTEGER
			MAX-ACCESS	read-only
			STATUS	current
			::= { hmWanMbusEC 31 }

hmWanMbusECVIF0D		OBJECT-TYPE
			SYNTAX	INTEGER
			MAX-ACCESS	read-only
			STATUS	current
			::= { hmWanMbusEC 32 }

hmWanMbusECValue0D		OBJECT-TYPE
			SYNTAX	INTEGER
			MAX-ACCESS	read-only
			STATUS	current
			::= { hmWanMbusEC 33 }

hmWanMbusECVIF0E		OBJECT-TYPE
			SYNTAX	INTEGER
			MAX-ACCESS	read-only
			STATUS	current
			::= { hmWanMbusEC 34 }

hmWanMbusECValue0E		OBJECT-TYPE
			SYNTAX	INTEGER
			MAX-ACCESS	read-only
			STATUS	current
			::= { hmWanMbusEC 35 }

hmWanMbusECVIF0F		OBJECT-TYPE
			SYNTAX	INTEGER
			MAX-ACCESS	read-only
			STATUS	current
			::= { hmWanMbusEC 36 }

hmWanMbusECValue0F		OBJECT-TYPE
			SYNTAX	INTEGER
			MAX-ACCESS	read-only
			STATUS	current
			::= { hmWanMbusEC 37 }

hmWanMbusECVIF10		OBJECT-TYPE
			SYNTAX	INTEGER
			MAX-ACCESS	read-only
			STATUS	current
			::= { hmWanMbusEC 38 }

hmWanMbusECValue10		OBJECT-TYPE
			SYNTAX	INTEGER
			MAX-ACCESS	read-only
			STATUS	current
			::= { hmWanMbusEC 39 }

hmWanMbusECVIF11		OBJECT-TYPE
			SYNTAX	INTEGER
			MAX-ACCESS	read-only
			STATUS	current
			::= { hmWanMbusEC 40 }

hmWanMbusECValue11		OBJECT-TYPE
			SYNTAX	INTEGER
			MAX-ACCESS	read-only
			STATUS	current
			::= { hmWanMbusEC 41 }

hmWanMbusECVIF12		OBJECT-TYPE
			SYNTAX	INTEGER
			MAX-ACCESS	read-only
			STATUS	current
			::= { hmWanMbusEC 42 }

hmWanMbusECValue12		OBJECT-TYPE
			SYNTAX	INTEGER
			MAX-ACCESS	read-only
			STATUS	current
			::= { hmWanMbusEC 43 }

hmWanMbusECVIF13		OBJECT-TYPE
			SYNTAX	INTEGER
			MAX-ACCESS	read-only
			STATUS	current
			::= { hmWanMbusEC 44 }

hmWanMbusECValue13		OBJECT-TYPE
			SYNTAX	INTEGER
			MAX-ACCESS	read-only
			STATUS	current
			::= { hmWanMbusEC 45 }

hmWanMbusECVIF14		OBJECT-TYPE
			SYNTAX	INTEGER
			MAX-ACCESS	read-only
			STATUS	current
			::= { hmWanMbusEC 46 }

hmWanMbusECValue14		OBJECT-TYPE
			SYNTAX	INTEGER
			MAX-ACCESS	read-only
			STATUS	current
			::= { hmWanMbusEC 47 }

hmWanMbusECVIF15		OBJECT-TYPE
			SYNTAX	INTEGER
			MAX-ACCESS	read-only
			STATUS	current
			::= { hmWanMbusEC 48 }

hmWanMbusECValue15		OBJECT-TYPE
			SYNTAX	INTEGER
			MAX-ACCESS	read-only
			STATUS	current
			::= { hmWanMbusEC 49 }

hmWanMbusECVIF16		OBJECT-TYPE
			SYNTAX	INTEGER
			MAX-ACCESS	read-only
			STATUS	current
			::= { hmWanMbusEC 50 }

hmWanMbusECValue16		OBJECT-TYPE
			SYNTAX	INTEGER
			MAX-ACCESS	read-only
			STATUS	current
			::= { hmWanMbusEC 51 }

hmWanMbusECVIF17		OBJECT-TYPE
			SYNTAX	INTEGER
			MAX-ACCESS	read-only
			STATUS	current
			::= { hmWanMbusEC 52 }

hmWanMbusECValue17		OBJECT-TYPE
			SYNTAX	INTEGER
			MAX-ACCESS	read-only
			STATUS	current
			::= { hmWanMbusEC 53 }

hmWanMbusECVIF18		OBJECT-TYPE
			SYNTAX	INTEGER
			MAX-ACCESS	read-only
			STATUS	current
			::= { hmWanMbusEC 54 }

hmWanMbusECValue18		OBJECT-TYPE
			SYNTAX	INTEGER
			MAX-ACCESS	read-only
			STATUS	current
			::= { hmWanMbusEC 55 }

hmWanMbusECVIF19		OBJECT-TYPE
			SYNTAX	INTEGER
			MAX-ACCESS	read-only
			STATUS	current
			::= { hmWanMbusEC 56 }

hmWanMbusECValue19		OBJECT-TYPE
			SYNTAX	INTEGER
			MAX-ACCESS	read-only
			STATUS	current
			::= { hmWanMbusEC 57 }

hmWanMbusECVIF1A		OBJECT-TYPE
			SYNTAX	INTEGER
			MAX-ACCESS	read-only
			STATUS	current
			::= { hmWanMbusEC 58 }

hmWanMbusECValue1A		OBJECT-TYPE
			SYNTAX	INTEGER
			MAX-ACCESS	read-only
			STATUS	current
			::= { hmWanMbusEC 59 }

hmWanMbusECVIF1B		OBJECT-TYPE
			SYNTAX	INTEGER
			MAX-ACCESS	read-only
			STATUS	current
			::= { hmWanMbusEC 60 }

hmWanMbusECValue1B		OBJECT-TYPE
			SYNTAX	INTEGER
			MAX-ACCESS	read-only
			STATUS	current
			::= { hmWanMbusEC 61 }

hmWanMbusECVIF1C		OBJECT-TYPE
			SYNTAX	INTEGER
			MAX-ACCESS	read-only
			STATUS	current
			::= { hmWanMbusEC 62 }

hmWanMbusECValue1C		OBJECT-TYPE
			SYNTAX	INTEGER
			MAX-ACCESS	read-only
			STATUS	current
			::= { hmWanMbusEC 63 }

hmWanMbusECVIF1D		OBJECT-TYPE
			SYNTAX	INTEGER
			MAX-ACCESS	read-only
			STATUS	current
			::= { hmWanMbusEC 64 }

hmWanMbusECValue1D		OBJECT-TYPE
			SYNTAX	INTEGER
			MAX-ACCESS	read-only
			STATUS	current
			::= { hmWanMbusEC 65 }

hmWanMbusECVIF1E		OBJECT-TYPE
			SYNTAX	INTEGER
			MAX-ACCESS	read-only
			STATUS	current
			::= { hmWanMbusEC 66 }

hmWanMbusECValue1E		OBJECT-TYPE
			SYNTAX	INTEGER
			MAX-ACCESS	read-only
			STATUS	current
			::= { hmWanMbusEC 67 }

hmWanMbusECVIF1F		OBJECT-TYPE
			SYNTAX	INTEGER
			MAX-ACCESS	read-only
			STATUS	current
			::= { hmWanMbusEC 68 }

hmWanMbusECValue1F		OBJECT-TYPE
			SYNTAX	INTEGER
			MAX-ACCESS	read-only
			STATUS	current
			::= { hmWanMbusEC 69 }

hmWanMbusECVIF20		OBJECT-TYPE
			SYNTAX	INTEGER
			MAX-ACCESS	read-only
			STATUS	current
			::= { hmWanMbusEC 70 }

hmWanMbusECValue20		OBJECT-TYPE
			SYNTAX	INTEGER
			MAX-ACCESS	read-only
			STATUS	current
			::= { hmWanMbusEC 71 }

hmWanMbusECVIF21		OBJECT-TYPE
			SYNTAX	INTEGER
			MAX-ACCESS	read-only
			STATUS	current
			::= { hmWanMbusEC 72 }

hmWanMbusECValue21		OBJECT-TYPE
			SYNTAX	INTEGER
			MAX-ACCESS	read-only
			STATUS	current
			::= { hmWanMbusEC 73 }

hmWanMbusECVIF22		OBJECT-TYPE
			SYNTAX	INTEGER
			MAX-ACCESS	read-only
			STATUS	current
			::= { hmWanMbusEC 74 }

hmWanMbusECValue22		OBJECT-TYPE
			SYNTAX	INTEGER
			MAX-ACCESS	read-only
			STATUS	current
			::= { hmWanMbusEC 75 }

hmWanMbusECVIF23		OBJECT-TYPE
			SYNTAX	INTEGER
			MAX-ACCESS	read-only
			STATUS	current
			::= { hmWanMbusEC 76 }

hmWanMbusECValue23		OBJECT-TYPE
			SYNTAX	INTEGER
			MAX-ACCESS	read-only
			STATUS	current
			::= { hmWanMbusEC 77 }

hmWanMbusECVIF24		OBJECT-TYPE
			SYNTAX	INTEGER
			MAX-ACCESS	read-only
			STATUS	current
			::= { hmWanMbusEC 78 }

hmWanMbusECValue24		OBJECT-TYPE
			SYNTAX	INTEGER
			MAX-ACCESS	read-only
			STATUS	current
			::= { hmWanMbusEC 79 }

hmWanMbusECVIF25		OBJECT-TYPE
			SYNTAX	INTEGER
			MAX-ACCESS	read-only
			STATUS	current
			::= { hmWanMbusEC 80 }

hmWanMbusECValue25		OBJECT-TYPE
			SYNTAX	INTEGER
			MAX-ACCESS	read-only
			STATUS	current
			::= { hmWanMbusEC 81 }

hmWanMbusECVIF26		OBJECT-TYPE
			SYNTAX	INTEGER
			MAX-ACCESS	read-only
			STATUS	current
			::= { hmWanMbusEC 82 }

hmWanMbusECValue26		OBJECT-TYPE
			SYNTAX	INTEGER
			MAX-ACCESS	read-only
			STATUS	current
			::= { hmWanMbusEC 83 }

hmWanMbusECVIF27		OBJECT-TYPE
			SYNTAX	INTEGER
			MAX-ACCESS	read-only
			STATUS	current
			::= { hmWanMbusEC 84 }

hmWanMbusECValue27		OBJECT-TYPE
			SYNTAX	INTEGER
			MAX-ACCESS	read-only
			STATUS	current
			::= { hmWanMbusEC 85 }

hmWanMbusECVIF28		OBJECT-TYPE
			SYNTAX	INTEGER
			MAX-ACCESS	read-only
			STATUS	current
			::= { hmWanMbusEC 86 }

hmWanMbusECValue28		OBJECT-TYPE
			SYNTAX	INTEGER
			MAX-ACCESS	read-only
			STATUS	current
			::= { hmWanMbusEC 87 }

hmWanMbusECVIF29		OBJECT-TYPE
			SYNTAX	INTEGER
			MAX-ACCESS	read-only
			STATUS	current
			::= { hmWanMbusEC 88 }

hmWanMbusECValue29		OBJECT-TYPE
			SYNTAX	INTEGER
			MAX-ACCESS	read-only
			STATUS	current
			::= { hmWanMbusEC 89 }

hmWanMbusECVIF2A		OBJECT-TYPE
			SYNTAX	INTEGER
			MAX-ACCESS	read-only
			STATUS	current
			::= { hmWanMbusEC 90 }

hmWanMbusECValue2A		OBJECT-TYPE
			SYNTAX	INTEGER
			MAX-ACCESS	read-only
			STATUS	current
			::= { hmWanMbusEC 91 }

hmWanMbusECVIF2B		OBJECT-TYPE
			SYNTAX	INTEGER
			MAX-ACCESS	read-only
			STATUS	current
			::= { hmWanMbusEC 92 }

hmWanMbusECValue2B		OBJECT-TYPE
			SYNTAX	INTEGER
			MAX-ACCESS	read-only
			STATUS	current
			::= { hmWanMbusEC 93 }

hmWanMbusECVIF2C		OBJECT-TYPE
			SYNTAX	INTEGER
			MAX-ACCESS	read-only
			STATUS	current
			::= { hmWanMbusEC 94 }

hmWanMbusECValue2C		OBJECT-TYPE
			SYNTAX	INTEGER
			MAX-ACCESS	read-only
			STATUS	current
			::= { hmWanMbusEC 95 }

hmWanMbusECVIF2D		OBJECT-TYPE
			SYNTAX	INTEGER
			MAX-ACCESS	read-only
			STATUS	current
			::= { hmWanMbusEC 96 }

hmWanMbusECValue2D		OBJECT-TYPE
			SYNTAX	INTEGER
			MAX-ACCESS	read-only
			STATUS	current
			::= { hmWanMbusEC 97 }

hmWanMbusECVIF2E		OBJECT-TYPE
			SYNTAX	INTEGER
			MAX-ACCESS	read-only
			STATUS	current
			::= { hmWanMbusEC 98 }

hmWanMbusECValue2E		OBJECT-TYPE
			SYNTAX	INTEGER
			MAX-ACCESS	read-only
			STATUS	current
			::= { hmWanMbusEC 99 }

hmWanMbusECVIF2F		OBJECT-TYPE
			SYNTAX	INTEGER
			MAX-ACCESS	read-only
			STATUS	current
			::= { hmWanMbusEC 100 }

hmWanMbusECValue2F		OBJECT-TYPE
			SYNTAX	INTEGER
			MAX-ACCESS	read-only
			STATUS	current
			::= { hmWanMbusEC 101 }

hmWanMbusED			OBJECT IDENTIFIER ::= { hmWanMbus 237 }

hmWanMbusEDIdNumber		OBJECT-TYPE
			SYNTAX	Gauge32
			MAX-ACCESS	read-only
			STATUS	current
			::= { hmWanMbusED 1 }

hmWanMbusEDManufacturer	OBJECT-TYPE
			SYNTAX	Gauge32
			MAX-ACCESS	read-only
			STATUS	current
			::= { hmWanMbusED 2 }

hmWanMbusEDVersion		OBJECT-TYPE
			SYNTAX	Gauge32
			MAX-ACCESS	read-only
			STATUS	current
			::= { hmWanMbusED 3 }

hmWanMbusEDMedium		OBJECT-TYPE
			SYNTAX	Gauge32
			MAX-ACCESS	read-only
			STATUS	current
			::= { hmWanMbusED 4 }

hmWanMbusEDStatus		OBJECT-TYPE
			SYNTAX	Gauge32
			MAX-ACCESS	read-only
			STATUS	current
			::= { hmWanMbusED 5 }

hmWanMbusEDVIF00		OBJECT-TYPE
			SYNTAX	INTEGER
			MAX-ACCESS	read-only
			STATUS	current
			::= { hmWanMbusED 6 }

hmWanMbusEDValue00		OBJECT-TYPE
			SYNTAX	INTEGER
			MAX-ACCESS	read-only
			STATUS	current
			::= { hmWanMbusED 7 }

hmWanMbusEDVIF01		OBJECT-TYPE
			SYNTAX	INTEGER
			MAX-ACCESS	read-only
			STATUS	current
			::= { hmWanMbusED 8 }

hmWanMbusEDValue01		OBJECT-TYPE
			SYNTAX	INTEGER
			MAX-ACCESS	read-only
			STATUS	current
			::= { hmWanMbusED 9 }

hmWanMbusEDVIF02		OBJECT-TYPE
			SYNTAX	INTEGER
			MAX-ACCESS	read-only
			STATUS	current
			::= { hmWanMbusED 10 }

hmWanMbusEDValue02		OBJECT-TYPE
			SYNTAX	INTEGER
			MAX-ACCESS	read-only
			STATUS	current
			::= { hmWanMbusED 11 }

hmWanMbusEDVIF03		OBJECT-TYPE
			SYNTAX	INTEGER
			MAX-ACCESS	read-only
			STATUS	current
			::= { hmWanMbusED 12 }

hmWanMbusEDValue03		OBJECT-TYPE
			SYNTAX	INTEGER
			MAX-ACCESS	read-only
			STATUS	current
			::= { hmWanMbusED 13 }

hmWanMbusEDVIF04		OBJECT-TYPE
			SYNTAX	INTEGER
			MAX-ACCESS	read-only
			STATUS	current
			::= { hmWanMbusED 14 }

hmWanMbusEDValue04		OBJECT-TYPE
			SYNTAX	INTEGER
			MAX-ACCESS	read-only
			STATUS	current
			::= { hmWanMbusED 15 }

hmWanMbusEDVIF05		OBJECT-TYPE
			SYNTAX	INTEGER
			MAX-ACCESS	read-only
			STATUS	current
			::= { hmWanMbusED 16 }

hmWanMbusEDValue05		OBJECT-TYPE
			SYNTAX	INTEGER
			MAX-ACCESS	read-only
			STATUS	current
			::= { hmWanMbusED 17 }

hmWanMbusEDVIF06		OBJECT-TYPE
			SYNTAX	INTEGER
			MAX-ACCESS	read-only
			STATUS	current
			::= { hmWanMbusED 18 }

hmWanMbusEDValue06		OBJECT-TYPE
			SYNTAX	INTEGER
			MAX-ACCESS	read-only
			STATUS	current
			::= { hmWanMbusED 19 }

hmWanMbusEDVIF07		OBJECT-TYPE
			SYNTAX	INTEGER
			MAX-ACCESS	read-only
			STATUS	current
			::= { hmWanMbusED 20 }

hmWanMbusEDValue07		OBJECT-TYPE
			SYNTAX	INTEGER
			MAX-ACCESS	read-only
			STATUS	current
			::= { hmWanMbusED 21 }

hmWanMbusEDVIF08		OBJECT-TYPE
			SYNTAX	INTEGER
			MAX-ACCESS	read-only
			STATUS	current
			::= { hmWanMbusED 22 }

hmWanMbusEDValue08		OBJECT-TYPE
			SYNTAX	INTEGER
			MAX-ACCESS	read-only
			STATUS	current
			::= { hmWanMbusED 23 }

hmWanMbusEDVIF09		OBJECT-TYPE
			SYNTAX	INTEGER
			MAX-ACCESS	read-only
			STATUS	current
			::= { hmWanMbusED 24 }

hmWanMbusEDValue09		OBJECT-TYPE
			SYNTAX	INTEGER
			MAX-ACCESS	read-only
			STATUS	current
			::= { hmWanMbusED 25 }

hmWanMbusEDVIF0A		OBJECT-TYPE
			SYNTAX	INTEGER
			MAX-ACCESS	read-only
			STATUS	current
			::= { hmWanMbusED 26 }

hmWanMbusEDValue0A		OBJECT-TYPE
			SYNTAX	INTEGER
			MAX-ACCESS	read-only
			STATUS	current
			::= { hmWanMbusED 27 }

hmWanMbusEDVIF0B		OBJECT-TYPE
			SYNTAX	INTEGER
			MAX-ACCESS	read-only
			STATUS	current
			::= { hmWanMbusED 28 }

hmWanMbusEDValue0B		OBJECT-TYPE
			SYNTAX	INTEGER
			MAX-ACCESS	read-only
			STATUS	current
			::= { hmWanMbusED 29 }

hmWanMbusEDVIF0C		OBJECT-TYPE
			SYNTAX	INTEGER
			MAX-ACCESS	read-only
			STATUS	current
			::= { hmWanMbusED 30 }

hmWanMbusEDValue0C		OBJECT-TYPE
			SYNTAX	INTEGER
			MAX-ACCESS	read-only
			STATUS	current
			::= { hmWanMbusED 31 }

hmWanMbusEDVIF0D		OBJECT-TYPE
			SYNTAX	INTEGER
			MAX-ACCESS	read-only
			STATUS	current
			::= { hmWanMbusED 32 }

hmWanMbusEDValue0D		OBJECT-TYPE
			SYNTAX	INTEGER
			MAX-ACCESS	read-only
			STATUS	current
			::= { hmWanMbusED 33 }

hmWanMbusEDVIF0E		OBJECT-TYPE
			SYNTAX	INTEGER
			MAX-ACCESS	read-only
			STATUS	current
			::= { hmWanMbusED 34 }

hmWanMbusEDValue0E		OBJECT-TYPE
			SYNTAX	INTEGER
			MAX-ACCESS	read-only
			STATUS	current
			::= { hmWanMbusED 35 }

hmWanMbusEDVIF0F		OBJECT-TYPE
			SYNTAX	INTEGER
			MAX-ACCESS	read-only
			STATUS	current
			::= { hmWanMbusED 36 }

hmWanMbusEDValue0F		OBJECT-TYPE
			SYNTAX	INTEGER
			MAX-ACCESS	read-only
			STATUS	current
			::= { hmWanMbusED 37 }

hmWanMbusEDVIF10		OBJECT-TYPE
			SYNTAX	INTEGER
			MAX-ACCESS	read-only
			STATUS	current
			::= { hmWanMbusED 38 }

hmWanMbusEDValue10		OBJECT-TYPE
			SYNTAX	INTEGER
			MAX-ACCESS	read-only
			STATUS	current
			::= { hmWanMbusED 39 }

hmWanMbusEDVIF11		OBJECT-TYPE
			SYNTAX	INTEGER
			MAX-ACCESS	read-only
			STATUS	current
			::= { hmWanMbusED 40 }

hmWanMbusEDValue11		OBJECT-TYPE
			SYNTAX	INTEGER
			MAX-ACCESS	read-only
			STATUS	current
			::= { hmWanMbusED 41 }

hmWanMbusEDVIF12		OBJECT-TYPE
			SYNTAX	INTEGER
			MAX-ACCESS	read-only
			STATUS	current
			::= { hmWanMbusED 42 }

hmWanMbusEDValue12		OBJECT-TYPE
			SYNTAX	INTEGER
			MAX-ACCESS	read-only
			STATUS	current
			::= { hmWanMbusED 43 }

hmWanMbusEDVIF13		OBJECT-TYPE
			SYNTAX	INTEGER
			MAX-ACCESS	read-only
			STATUS	current
			::= { hmWanMbusED 44 }

hmWanMbusEDValue13		OBJECT-TYPE
			SYNTAX	INTEGER
			MAX-ACCESS	read-only
			STATUS	current
			::= { hmWanMbusED 45 }

hmWanMbusEDVIF14		OBJECT-TYPE
			SYNTAX	INTEGER
			MAX-ACCESS	read-only
			STATUS	current
			::= { hmWanMbusED 46 }

hmWanMbusEDValue14		OBJECT-TYPE
			SYNTAX	INTEGER
			MAX-ACCESS	read-only
			STATUS	current
			::= { hmWanMbusED 47 }

hmWanMbusEDVIF15		OBJECT-TYPE
			SYNTAX	INTEGER
			MAX-ACCESS	read-only
			STATUS	current
			::= { hmWanMbusED 48 }

hmWanMbusEDValue15		OBJECT-TYPE
			SYNTAX	INTEGER
			MAX-ACCESS	read-only
			STATUS	current
			::= { hmWanMbusED 49 }

hmWanMbusEDVIF16		OBJECT-TYPE
			SYNTAX	INTEGER
			MAX-ACCESS	read-only
			STATUS	current
			::= { hmWanMbusED 50 }

hmWanMbusEDValue16		OBJECT-TYPE
			SYNTAX	INTEGER
			MAX-ACCESS	read-only
			STATUS	current
			::= { hmWanMbusED 51 }

hmWanMbusEDVIF17		OBJECT-TYPE
			SYNTAX	INTEGER
			MAX-ACCESS	read-only
			STATUS	current
			::= { hmWanMbusED 52 }

hmWanMbusEDValue17		OBJECT-TYPE
			SYNTAX	INTEGER
			MAX-ACCESS	read-only
			STATUS	current
			::= { hmWanMbusED 53 }

hmWanMbusEDVIF18		OBJECT-TYPE
			SYNTAX	INTEGER
			MAX-ACCESS	read-only
			STATUS	current
			::= { hmWanMbusED 54 }

hmWanMbusEDValue18		OBJECT-TYPE
			SYNTAX	INTEGER
			MAX-ACCESS	read-only
			STATUS	current
			::= { hmWanMbusED 55 }

hmWanMbusEDVIF19		OBJECT-TYPE
			SYNTAX	INTEGER
			MAX-ACCESS	read-only
			STATUS	current
			::= { hmWanMbusED 56 }

hmWanMbusEDValue19		OBJECT-TYPE
			SYNTAX	INTEGER
			MAX-ACCESS	read-only
			STATUS	current
			::= { hmWanMbusED 57 }

hmWanMbusEDVIF1A		OBJECT-TYPE
			SYNTAX	INTEGER
			MAX-ACCESS	read-only
			STATUS	current
			::= { hmWanMbusED 58 }

hmWanMbusEDValue1A		OBJECT-TYPE
			SYNTAX	INTEGER
			MAX-ACCESS	read-only
			STATUS	current
			::= { hmWanMbusED 59 }

hmWanMbusEDVIF1B		OBJECT-TYPE
			SYNTAX	INTEGER
			MAX-ACCESS	read-only
			STATUS	current
			::= { hmWanMbusED 60 }

hmWanMbusEDValue1B		OBJECT-TYPE
			SYNTAX	INTEGER
			MAX-ACCESS	read-only
			STATUS	current
			::= { hmWanMbusED 61 }

hmWanMbusEDVIF1C		OBJECT-TYPE
			SYNTAX	INTEGER
			MAX-ACCESS	read-only
			STATUS	current
			::= { hmWanMbusED 62 }

hmWanMbusEDValue1C		OBJECT-TYPE
			SYNTAX	INTEGER
			MAX-ACCESS	read-only
			STATUS	current
			::= { hmWanMbusED 63 }

hmWanMbusEDVIF1D		OBJECT-TYPE
			SYNTAX	INTEGER
			MAX-ACCESS	read-only
			STATUS	current
			::= { hmWanMbusED 64 }

hmWanMbusEDValue1D		OBJECT-TYPE
			SYNTAX	INTEGER
			MAX-ACCESS	read-only
			STATUS	current
			::= { hmWanMbusED 65 }

hmWanMbusEDVIF1E		OBJECT-TYPE
			SYNTAX	INTEGER
			MAX-ACCESS	read-only
			STATUS	current
			::= { hmWanMbusED 66 }

hmWanMbusEDValue1E		OBJECT-TYPE
			SYNTAX	INTEGER
			MAX-ACCESS	read-only
			STATUS	current
			::= { hmWanMbusED 67 }

hmWanMbusEDVIF1F		OBJECT-TYPE
			SYNTAX	INTEGER
			MAX-ACCESS	read-only
			STATUS	current
			::= { hmWanMbusED 68 }

hmWanMbusEDValue1F		OBJECT-TYPE
			SYNTAX	INTEGER
			MAX-ACCESS	read-only
			STATUS	current
			::= { hmWanMbusED 69 }

hmWanMbusEDVIF20		OBJECT-TYPE
			SYNTAX	INTEGER
			MAX-ACCESS	read-only
			STATUS	current
			::= { hmWanMbusED 70 }

hmWanMbusEDValue20		OBJECT-TYPE
			SYNTAX	INTEGER
			MAX-ACCESS	read-only
			STATUS	current
			::= { hmWanMbusED 71 }

hmWanMbusEDVIF21		OBJECT-TYPE
			SYNTAX	INTEGER
			MAX-ACCESS	read-only
			STATUS	current
			::= { hmWanMbusED 72 }

hmWanMbusEDValue21		OBJECT-TYPE
			SYNTAX	INTEGER
			MAX-ACCESS	read-only
			STATUS	current
			::= { hmWanMbusED 73 }

hmWanMbusEDVIF22		OBJECT-TYPE
			SYNTAX	INTEGER
			MAX-ACCESS	read-only
			STATUS	current
			::= { hmWanMbusED 74 }

hmWanMbusEDValue22		OBJECT-TYPE
			SYNTAX	INTEGER
			MAX-ACCESS	read-only
			STATUS	current
			::= { hmWanMbusED 75 }

hmWanMbusEDVIF23		OBJECT-TYPE
			SYNTAX	INTEGER
			MAX-ACCESS	read-only
			STATUS	current
			::= { hmWanMbusED 76 }

hmWanMbusEDValue23		OBJECT-TYPE
			SYNTAX	INTEGER
			MAX-ACCESS	read-only
			STATUS	current
			::= { hmWanMbusED 77 }

hmWanMbusEDVIF24		OBJECT-TYPE
			SYNTAX	INTEGER
			MAX-ACCESS	read-only
			STATUS	current
			::= { hmWanMbusED 78 }

hmWanMbusEDValue24		OBJECT-TYPE
			SYNTAX	INTEGER
			MAX-ACCESS	read-only
			STATUS	current
			::= { hmWanMbusED 79 }

hmWanMbusEDVIF25		OBJECT-TYPE
			SYNTAX	INTEGER
			MAX-ACCESS	read-only
			STATUS	current
			::= { hmWanMbusED 80 }

hmWanMbusEDValue25		OBJECT-TYPE
			SYNTAX	INTEGER
			MAX-ACCESS	read-only
			STATUS	current
			::= { hmWanMbusED 81 }

hmWanMbusEDVIF26		OBJECT-TYPE
			SYNTAX	INTEGER
			MAX-ACCESS	read-only
			STATUS	current
			::= { hmWanMbusED 82 }

hmWanMbusEDValue26		OBJECT-TYPE
			SYNTAX	INTEGER
			MAX-ACCESS	read-only
			STATUS	current
			::= { hmWanMbusED 83 }

hmWanMbusEDVIF27		OBJECT-TYPE
			SYNTAX	INTEGER
			MAX-ACCESS	read-only
			STATUS	current
			::= { hmWanMbusED 84 }

hmWanMbusEDValue27		OBJECT-TYPE
			SYNTAX	INTEGER
			MAX-ACCESS	read-only
			STATUS	current
			::= { hmWanMbusED 85 }

hmWanMbusEDVIF28		OBJECT-TYPE
			SYNTAX	INTEGER
			MAX-ACCESS	read-only
			STATUS	current
			::= { hmWanMbusED 86 }

hmWanMbusEDValue28		OBJECT-TYPE
			SYNTAX	INTEGER
			MAX-ACCESS	read-only
			STATUS	current
			::= { hmWanMbusED 87 }

hmWanMbusEDVIF29		OBJECT-TYPE
			SYNTAX	INTEGER
			MAX-ACCESS	read-only
			STATUS	current
			::= { hmWanMbusED 88 }

hmWanMbusEDValue29		OBJECT-TYPE
			SYNTAX	INTEGER
			MAX-ACCESS	read-only
			STATUS	current
			::= { hmWanMbusED 89 }

hmWanMbusEDVIF2A		OBJECT-TYPE
			SYNTAX	INTEGER
			MAX-ACCESS	read-only
			STATUS	current
			::= { hmWanMbusED 90 }

hmWanMbusEDValue2A		OBJECT-TYPE
			SYNTAX	INTEGER
			MAX-ACCESS	read-only
			STATUS	current
			::= { hmWanMbusED 91 }

hmWanMbusEDVIF2B		OBJECT-TYPE
			SYNTAX	INTEGER
			MAX-ACCESS	read-only
			STATUS	current
			::= { hmWanMbusED 92 }

hmWanMbusEDValue2B		OBJECT-TYPE
			SYNTAX	INTEGER
			MAX-ACCESS	read-only
			STATUS	current
			::= { hmWanMbusED 93 }

hmWanMbusEDVIF2C		OBJECT-TYPE
			SYNTAX	INTEGER
			MAX-ACCESS	read-only
			STATUS	current
			::= { hmWanMbusED 94 }

hmWanMbusEDValue2C		OBJECT-TYPE
			SYNTAX	INTEGER
			MAX-ACCESS	read-only
			STATUS	current
			::= { hmWanMbusED 95 }

hmWanMbusEDVIF2D		OBJECT-TYPE
			SYNTAX	INTEGER
			MAX-ACCESS	read-only
			STATUS	current
			::= { hmWanMbusED 96 }

hmWanMbusEDValue2D		OBJECT-TYPE
			SYNTAX	INTEGER
			MAX-ACCESS	read-only
			STATUS	current
			::= { hmWanMbusED 97 }

hmWanMbusEDVIF2E		OBJECT-TYPE
			SYNTAX	INTEGER
			MAX-ACCESS	read-only
			STATUS	current
			::= { hmWanMbusED 98 }

hmWanMbusEDValue2E		OBJECT-TYPE
			SYNTAX	INTEGER
			MAX-ACCESS	read-only
			STATUS	current
			::= { hmWanMbusED 99 }

hmWanMbusEDVIF2F		OBJECT-TYPE
			SYNTAX	INTEGER
			MAX-ACCESS	read-only
			STATUS	current
			::= { hmWanMbusED 100 }

hmWanMbusEDValue2F		OBJECT-TYPE
			SYNTAX	INTEGER
			MAX-ACCESS	read-only
			STATUS	current
			::= { hmWanMbusED 101 }

hmWanMbusEE			OBJECT IDENTIFIER ::= { hmWanMbus 238 }

hmWanMbusEEIdNumber		OBJECT-TYPE
			SYNTAX	Gauge32
			MAX-ACCESS	read-only
			STATUS	current
			::= { hmWanMbusEE 1 }

hmWanMbusEEManufacturer	OBJECT-TYPE
			SYNTAX	Gauge32
			MAX-ACCESS	read-only
			STATUS	current
			::= { hmWanMbusEE 2 }

hmWanMbusEEVersion		OBJECT-TYPE
			SYNTAX	Gauge32
			MAX-ACCESS	read-only
			STATUS	current
			::= { hmWanMbusEE 3 }

hmWanMbusEEMedium		OBJECT-TYPE
			SYNTAX	Gauge32
			MAX-ACCESS	read-only
			STATUS	current
			::= { hmWanMbusEE 4 }

hmWanMbusEEStatus		OBJECT-TYPE
			SYNTAX	Gauge32
			MAX-ACCESS	read-only
			STATUS	current
			::= { hmWanMbusEE 5 }

hmWanMbusEEVIF00		OBJECT-TYPE
			SYNTAX	INTEGER
			MAX-ACCESS	read-only
			STATUS	current
			::= { hmWanMbusEE 6 }

hmWanMbusEEValue00		OBJECT-TYPE
			SYNTAX	INTEGER
			MAX-ACCESS	read-only
			STATUS	current
			::= { hmWanMbusEE 7 }

hmWanMbusEEVIF01		OBJECT-TYPE
			SYNTAX	INTEGER
			MAX-ACCESS	read-only
			STATUS	current
			::= { hmWanMbusEE 8 }

hmWanMbusEEValue01		OBJECT-TYPE
			SYNTAX	INTEGER
			MAX-ACCESS	read-only
			STATUS	current
			::= { hmWanMbusEE 9 }

hmWanMbusEEVIF02		OBJECT-TYPE
			SYNTAX	INTEGER
			MAX-ACCESS	read-only
			STATUS	current
			::= { hmWanMbusEE 10 }

hmWanMbusEEValue02		OBJECT-TYPE
			SYNTAX	INTEGER
			MAX-ACCESS	read-only
			STATUS	current
			::= { hmWanMbusEE 11 }

hmWanMbusEEVIF03		OBJECT-TYPE
			SYNTAX	INTEGER
			MAX-ACCESS	read-only
			STATUS	current
			::= { hmWanMbusEE 12 }

hmWanMbusEEValue03		OBJECT-TYPE
			SYNTAX	INTEGER
			MAX-ACCESS	read-only
			STATUS	current
			::= { hmWanMbusEE 13 }

hmWanMbusEEVIF04		OBJECT-TYPE
			SYNTAX	INTEGER
			MAX-ACCESS	read-only
			STATUS	current
			::= { hmWanMbusEE 14 }

hmWanMbusEEValue04		OBJECT-TYPE
			SYNTAX	INTEGER
			MAX-ACCESS	read-only
			STATUS	current
			::= { hmWanMbusEE 15 }

hmWanMbusEEVIF05		OBJECT-TYPE
			SYNTAX	INTEGER
			MAX-ACCESS	read-only
			STATUS	current
			::= { hmWanMbusEE 16 }

hmWanMbusEEValue05		OBJECT-TYPE
			SYNTAX	INTEGER
			MAX-ACCESS	read-only
			STATUS	current
			::= { hmWanMbusEE 17 }

hmWanMbusEEVIF06		OBJECT-TYPE
			SYNTAX	INTEGER
			MAX-ACCESS	read-only
			STATUS	current
			::= { hmWanMbusEE 18 }

hmWanMbusEEValue06		OBJECT-TYPE
			SYNTAX	INTEGER
			MAX-ACCESS	read-only
			STATUS	current
			::= { hmWanMbusEE 19 }

hmWanMbusEEVIF07		OBJECT-TYPE
			SYNTAX	INTEGER
			MAX-ACCESS	read-only
			STATUS	current
			::= { hmWanMbusEE 20 }

hmWanMbusEEValue07		OBJECT-TYPE
			SYNTAX	INTEGER
			MAX-ACCESS	read-only
			STATUS	current
			::= { hmWanMbusEE 21 }

hmWanMbusEEVIF08		OBJECT-TYPE
			SYNTAX	INTEGER
			MAX-ACCESS	read-only
			STATUS	current
			::= { hmWanMbusEE 22 }

hmWanMbusEEValue08		OBJECT-TYPE
			SYNTAX	INTEGER
			MAX-ACCESS	read-only
			STATUS	current
			::= { hmWanMbusEE 23 }

hmWanMbusEEVIF09		OBJECT-TYPE
			SYNTAX	INTEGER
			MAX-ACCESS	read-only
			STATUS	current
			::= { hmWanMbusEE 24 }

hmWanMbusEEValue09		OBJECT-TYPE
			SYNTAX	INTEGER
			MAX-ACCESS	read-only
			STATUS	current
			::= { hmWanMbusEE 25 }

hmWanMbusEEVIF0A		OBJECT-TYPE
			SYNTAX	INTEGER
			MAX-ACCESS	read-only
			STATUS	current
			::= { hmWanMbusEE 26 }

hmWanMbusEEValue0A		OBJECT-TYPE
			SYNTAX	INTEGER
			MAX-ACCESS	read-only
			STATUS	current
			::= { hmWanMbusEE 27 }

hmWanMbusEEVIF0B		OBJECT-TYPE
			SYNTAX	INTEGER
			MAX-ACCESS	read-only
			STATUS	current
			::= { hmWanMbusEE 28 }

hmWanMbusEEValue0B		OBJECT-TYPE
			SYNTAX	INTEGER
			MAX-ACCESS	read-only
			STATUS	current
			::= { hmWanMbusEE 29 }

hmWanMbusEEVIF0C		OBJECT-TYPE
			SYNTAX	INTEGER
			MAX-ACCESS	read-only
			STATUS	current
			::= { hmWanMbusEE 30 }

hmWanMbusEEValue0C		OBJECT-TYPE
			SYNTAX	INTEGER
			MAX-ACCESS	read-only
			STATUS	current
			::= { hmWanMbusEE 31 }

hmWanMbusEEVIF0D		OBJECT-TYPE
			SYNTAX	INTEGER
			MAX-ACCESS	read-only
			STATUS	current
			::= { hmWanMbusEE 32 }

hmWanMbusEEValue0D		OBJECT-TYPE
			SYNTAX	INTEGER
			MAX-ACCESS	read-only
			STATUS	current
			::= { hmWanMbusEE 33 }

hmWanMbusEEVIF0E		OBJECT-TYPE
			SYNTAX	INTEGER
			MAX-ACCESS	read-only
			STATUS	current
			::= { hmWanMbusEE 34 }

hmWanMbusEEValue0E		OBJECT-TYPE
			SYNTAX	INTEGER
			MAX-ACCESS	read-only
			STATUS	current
			::= { hmWanMbusEE 35 }

hmWanMbusEEVIF0F		OBJECT-TYPE
			SYNTAX	INTEGER
			MAX-ACCESS	read-only
			STATUS	current
			::= { hmWanMbusEE 36 }

hmWanMbusEEValue0F		OBJECT-TYPE
			SYNTAX	INTEGER
			MAX-ACCESS	read-only
			STATUS	current
			::= { hmWanMbusEE 37 }

hmWanMbusEEVIF10		OBJECT-TYPE
			SYNTAX	INTEGER
			MAX-ACCESS	read-only
			STATUS	current
			::= { hmWanMbusEE 38 }

hmWanMbusEEValue10		OBJECT-TYPE
			SYNTAX	INTEGER
			MAX-ACCESS	read-only
			STATUS	current
			::= { hmWanMbusEE 39 }

hmWanMbusEEVIF11		OBJECT-TYPE
			SYNTAX	INTEGER
			MAX-ACCESS	read-only
			STATUS	current
			::= { hmWanMbusEE 40 }

hmWanMbusEEValue11		OBJECT-TYPE
			SYNTAX	INTEGER
			MAX-ACCESS	read-only
			STATUS	current
			::= { hmWanMbusEE 41 }

hmWanMbusEEVIF12		OBJECT-TYPE
			SYNTAX	INTEGER
			MAX-ACCESS	read-only
			STATUS	current
			::= { hmWanMbusEE 42 }

hmWanMbusEEValue12		OBJECT-TYPE
			SYNTAX	INTEGER
			MAX-ACCESS	read-only
			STATUS	current
			::= { hmWanMbusEE 43 }

hmWanMbusEEVIF13		OBJECT-TYPE
			SYNTAX	INTEGER
			MAX-ACCESS	read-only
			STATUS	current
			::= { hmWanMbusEE 44 }

hmWanMbusEEValue13		OBJECT-TYPE
			SYNTAX	INTEGER
			MAX-ACCESS	read-only
			STATUS	current
			::= { hmWanMbusEE 45 }

hmWanMbusEEVIF14		OBJECT-TYPE
			SYNTAX	INTEGER
			MAX-ACCESS	read-only
			STATUS	current
			::= { hmWanMbusEE 46 }

hmWanMbusEEValue14		OBJECT-TYPE
			SYNTAX	INTEGER
			MAX-ACCESS	read-only
			STATUS	current
			::= { hmWanMbusEE 47 }

hmWanMbusEEVIF15		OBJECT-TYPE
			SYNTAX	INTEGER
			MAX-ACCESS	read-only
			STATUS	current
			::= { hmWanMbusEE 48 }

hmWanMbusEEValue15		OBJECT-TYPE
			SYNTAX	INTEGER
			MAX-ACCESS	read-only
			STATUS	current
			::= { hmWanMbusEE 49 }

hmWanMbusEEVIF16		OBJECT-TYPE
			SYNTAX	INTEGER
			MAX-ACCESS	read-only
			STATUS	current
			::= { hmWanMbusEE 50 }

hmWanMbusEEValue16		OBJECT-TYPE
			SYNTAX	INTEGER
			MAX-ACCESS	read-only
			STATUS	current
			::= { hmWanMbusEE 51 }

hmWanMbusEEVIF17		OBJECT-TYPE
			SYNTAX	INTEGER
			MAX-ACCESS	read-only
			STATUS	current
			::= { hmWanMbusEE 52 }

hmWanMbusEEValue17		OBJECT-TYPE
			SYNTAX	INTEGER
			MAX-ACCESS	read-only
			STATUS	current
			::= { hmWanMbusEE 53 }

hmWanMbusEEVIF18		OBJECT-TYPE
			SYNTAX	INTEGER
			MAX-ACCESS	read-only
			STATUS	current
			::= { hmWanMbusEE 54 }

hmWanMbusEEValue18		OBJECT-TYPE
			SYNTAX	INTEGER
			MAX-ACCESS	read-only
			STATUS	current
			::= { hmWanMbusEE 55 }

hmWanMbusEEVIF19		OBJECT-TYPE
			SYNTAX	INTEGER
			MAX-ACCESS	read-only
			STATUS	current
			::= { hmWanMbusEE 56 }

hmWanMbusEEValue19		OBJECT-TYPE
			SYNTAX	INTEGER
			MAX-ACCESS	read-only
			STATUS	current
			::= { hmWanMbusEE 57 }

hmWanMbusEEVIF1A		OBJECT-TYPE
			SYNTAX	INTEGER
			MAX-ACCESS	read-only
			STATUS	current
			::= { hmWanMbusEE 58 }

hmWanMbusEEValue1A		OBJECT-TYPE
			SYNTAX	INTEGER
			MAX-ACCESS	read-only
			STATUS	current
			::= { hmWanMbusEE 59 }

hmWanMbusEEVIF1B		OBJECT-TYPE
			SYNTAX	INTEGER
			MAX-ACCESS	read-only
			STATUS	current
			::= { hmWanMbusEE 60 }

hmWanMbusEEValue1B		OBJECT-TYPE
			SYNTAX	INTEGER
			MAX-ACCESS	read-only
			STATUS	current
			::= { hmWanMbusEE 61 }

hmWanMbusEEVIF1C		OBJECT-TYPE
			SYNTAX	INTEGER
			MAX-ACCESS	read-only
			STATUS	current
			::= { hmWanMbusEE 62 }

hmWanMbusEEValue1C		OBJECT-TYPE
			SYNTAX	INTEGER
			MAX-ACCESS	read-only
			STATUS	current
			::= { hmWanMbusEE 63 }

hmWanMbusEEVIF1D		OBJECT-TYPE
			SYNTAX	INTEGER
			MAX-ACCESS	read-only
			STATUS	current
			::= { hmWanMbusEE 64 }

hmWanMbusEEValue1D		OBJECT-TYPE
			SYNTAX	INTEGER
			MAX-ACCESS	read-only
			STATUS	current
			::= { hmWanMbusEE 65 }

hmWanMbusEEVIF1E		OBJECT-TYPE
			SYNTAX	INTEGER
			MAX-ACCESS	read-only
			STATUS	current
			::= { hmWanMbusEE 66 }

hmWanMbusEEValue1E		OBJECT-TYPE
			SYNTAX	INTEGER
			MAX-ACCESS	read-only
			STATUS	current
			::= { hmWanMbusEE 67 }

hmWanMbusEEVIF1F		OBJECT-TYPE
			SYNTAX	INTEGER
			MAX-ACCESS	read-only
			STATUS	current
			::= { hmWanMbusEE 68 }

hmWanMbusEEValue1F		OBJECT-TYPE
			SYNTAX	INTEGER
			MAX-ACCESS	read-only
			STATUS	current
			::= { hmWanMbusEE 69 }

hmWanMbusEEVIF20		OBJECT-TYPE
			SYNTAX	INTEGER
			MAX-ACCESS	read-only
			STATUS	current
			::= { hmWanMbusEE 70 }

hmWanMbusEEValue20		OBJECT-TYPE
			SYNTAX	INTEGER
			MAX-ACCESS	read-only
			STATUS	current
			::= { hmWanMbusEE 71 }

hmWanMbusEEVIF21		OBJECT-TYPE
			SYNTAX	INTEGER
			MAX-ACCESS	read-only
			STATUS	current
			::= { hmWanMbusEE 72 }

hmWanMbusEEValue21		OBJECT-TYPE
			SYNTAX	INTEGER
			MAX-ACCESS	read-only
			STATUS	current
			::= { hmWanMbusEE 73 }

hmWanMbusEEVIF22		OBJECT-TYPE
			SYNTAX	INTEGER
			MAX-ACCESS	read-only
			STATUS	current
			::= { hmWanMbusEE 74 }

hmWanMbusEEValue22		OBJECT-TYPE
			SYNTAX	INTEGER
			MAX-ACCESS	read-only
			STATUS	current
			::= { hmWanMbusEE 75 }

hmWanMbusEEVIF23		OBJECT-TYPE
			SYNTAX	INTEGER
			MAX-ACCESS	read-only
			STATUS	current
			::= { hmWanMbusEE 76 }

hmWanMbusEEValue23		OBJECT-TYPE
			SYNTAX	INTEGER
			MAX-ACCESS	read-only
			STATUS	current
			::= { hmWanMbusEE 77 }

hmWanMbusEEVIF24		OBJECT-TYPE
			SYNTAX	INTEGER
			MAX-ACCESS	read-only
			STATUS	current
			::= { hmWanMbusEE 78 }

hmWanMbusEEValue24		OBJECT-TYPE
			SYNTAX	INTEGER
			MAX-ACCESS	read-only
			STATUS	current
			::= { hmWanMbusEE 79 }

hmWanMbusEEVIF25		OBJECT-TYPE
			SYNTAX	INTEGER
			MAX-ACCESS	read-only
			STATUS	current
			::= { hmWanMbusEE 80 }

hmWanMbusEEValue25		OBJECT-TYPE
			SYNTAX	INTEGER
			MAX-ACCESS	read-only
			STATUS	current
			::= { hmWanMbusEE 81 }

hmWanMbusEEVIF26		OBJECT-TYPE
			SYNTAX	INTEGER
			MAX-ACCESS	read-only
			STATUS	current
			::= { hmWanMbusEE 82 }

hmWanMbusEEValue26		OBJECT-TYPE
			SYNTAX	INTEGER
			MAX-ACCESS	read-only
			STATUS	current
			::= { hmWanMbusEE 83 }

hmWanMbusEEVIF27		OBJECT-TYPE
			SYNTAX	INTEGER
			MAX-ACCESS	read-only
			STATUS	current
			::= { hmWanMbusEE 84 }

hmWanMbusEEValue27		OBJECT-TYPE
			SYNTAX	INTEGER
			MAX-ACCESS	read-only
			STATUS	current
			::= { hmWanMbusEE 85 }

hmWanMbusEEVIF28		OBJECT-TYPE
			SYNTAX	INTEGER
			MAX-ACCESS	read-only
			STATUS	current
			::= { hmWanMbusEE 86 }

hmWanMbusEEValue28		OBJECT-TYPE
			SYNTAX	INTEGER
			MAX-ACCESS	read-only
			STATUS	current
			::= { hmWanMbusEE 87 }

hmWanMbusEEVIF29		OBJECT-TYPE
			SYNTAX	INTEGER
			MAX-ACCESS	read-only
			STATUS	current
			::= { hmWanMbusEE 88 }

hmWanMbusEEValue29		OBJECT-TYPE
			SYNTAX	INTEGER
			MAX-ACCESS	read-only
			STATUS	current
			::= { hmWanMbusEE 89 }

hmWanMbusEEVIF2A		OBJECT-TYPE
			SYNTAX	INTEGER
			MAX-ACCESS	read-only
			STATUS	current
			::= { hmWanMbusEE 90 }

hmWanMbusEEValue2A		OBJECT-TYPE
			SYNTAX	INTEGER
			MAX-ACCESS	read-only
			STATUS	current
			::= { hmWanMbusEE 91 }

hmWanMbusEEVIF2B		OBJECT-TYPE
			SYNTAX	INTEGER
			MAX-ACCESS	read-only
			STATUS	current
			::= { hmWanMbusEE 92 }

hmWanMbusEEValue2B		OBJECT-TYPE
			SYNTAX	INTEGER
			MAX-ACCESS	read-only
			STATUS	current
			::= { hmWanMbusEE 93 }

hmWanMbusEEVIF2C		OBJECT-TYPE
			SYNTAX	INTEGER
			MAX-ACCESS	read-only
			STATUS	current
			::= { hmWanMbusEE 94 }

hmWanMbusEEValue2C		OBJECT-TYPE
			SYNTAX	INTEGER
			MAX-ACCESS	read-only
			STATUS	current
			::= { hmWanMbusEE 95 }

hmWanMbusEEVIF2D		OBJECT-TYPE
			SYNTAX	INTEGER
			MAX-ACCESS	read-only
			STATUS	current
			::= { hmWanMbusEE 96 }

hmWanMbusEEValue2D		OBJECT-TYPE
			SYNTAX	INTEGER
			MAX-ACCESS	read-only
			STATUS	current
			::= { hmWanMbusEE 97 }

hmWanMbusEEVIF2E		OBJECT-TYPE
			SYNTAX	INTEGER
			MAX-ACCESS	read-only
			STATUS	current
			::= { hmWanMbusEE 98 }

hmWanMbusEEValue2E		OBJECT-TYPE
			SYNTAX	INTEGER
			MAX-ACCESS	read-only
			STATUS	current
			::= { hmWanMbusEE 99 }

hmWanMbusEEVIF2F		OBJECT-TYPE
			SYNTAX	INTEGER
			MAX-ACCESS	read-only
			STATUS	current
			::= { hmWanMbusEE 100 }

hmWanMbusEEValue2F		OBJECT-TYPE
			SYNTAX	INTEGER
			MAX-ACCESS	read-only
			STATUS	current
			::= { hmWanMbusEE 101 }

hmWanMbusEF			OBJECT IDENTIFIER ::= { hmWanMbus 239 }

hmWanMbusEFIdNumber		OBJECT-TYPE
			SYNTAX	Gauge32
			MAX-ACCESS	read-only
			STATUS	current
			::= { hmWanMbusEF 1 }

hmWanMbusEFManufacturer	OBJECT-TYPE
			SYNTAX	Gauge32
			MAX-ACCESS	read-only
			STATUS	current
			::= { hmWanMbusEF 2 }

hmWanMbusEFVersion		OBJECT-TYPE
			SYNTAX	Gauge32
			MAX-ACCESS	read-only
			STATUS	current
			::= { hmWanMbusEF 3 }

hmWanMbusEFMedium		OBJECT-TYPE
			SYNTAX	Gauge32
			MAX-ACCESS	read-only
			STATUS	current
			::= { hmWanMbusEF 4 }

hmWanMbusEFStatus		OBJECT-TYPE
			SYNTAX	Gauge32
			MAX-ACCESS	read-only
			STATUS	current
			::= { hmWanMbusEF 5 }

hmWanMbusEFVIF00		OBJECT-TYPE
			SYNTAX	INTEGER
			MAX-ACCESS	read-only
			STATUS	current
			::= { hmWanMbusEF 6 }

hmWanMbusEFValue00		OBJECT-TYPE
			SYNTAX	INTEGER
			MAX-ACCESS	read-only
			STATUS	current
			::= { hmWanMbusEF 7 }

hmWanMbusEFVIF01		OBJECT-TYPE
			SYNTAX	INTEGER
			MAX-ACCESS	read-only
			STATUS	current
			::= { hmWanMbusEF 8 }

hmWanMbusEFValue01		OBJECT-TYPE
			SYNTAX	INTEGER
			MAX-ACCESS	read-only
			STATUS	current
			::= { hmWanMbusEF 9 }

hmWanMbusEFVIF02		OBJECT-TYPE
			SYNTAX	INTEGER
			MAX-ACCESS	read-only
			STATUS	current
			::= { hmWanMbusEF 10 }

hmWanMbusEFValue02		OBJECT-TYPE
			SYNTAX	INTEGER
			MAX-ACCESS	read-only
			STATUS	current
			::= { hmWanMbusEF 11 }

hmWanMbusEFVIF03		OBJECT-TYPE
			SYNTAX	INTEGER
			MAX-ACCESS	read-only
			STATUS	current
			::= { hmWanMbusEF 12 }

hmWanMbusEFValue03		OBJECT-TYPE
			SYNTAX	INTEGER
			MAX-ACCESS	read-only
			STATUS	current
			::= { hmWanMbusEF 13 }

hmWanMbusEFVIF04		OBJECT-TYPE
			SYNTAX	INTEGER
			MAX-ACCESS	read-only
			STATUS	current
			::= { hmWanMbusEF 14 }

hmWanMbusEFValue04		OBJECT-TYPE
			SYNTAX	INTEGER
			MAX-ACCESS	read-only
			STATUS	current
			::= { hmWanMbusEF 15 }

hmWanMbusEFVIF05		OBJECT-TYPE
			SYNTAX	INTEGER
			MAX-ACCESS	read-only
			STATUS	current
			::= { hmWanMbusEF 16 }

hmWanMbusEFValue05		OBJECT-TYPE
			SYNTAX	INTEGER
			MAX-ACCESS	read-only
			STATUS	current
			::= { hmWanMbusEF 17 }

hmWanMbusEFVIF06		OBJECT-TYPE
			SYNTAX	INTEGER
			MAX-ACCESS	read-only
			STATUS	current
			::= { hmWanMbusEF 18 }

hmWanMbusEFValue06		OBJECT-TYPE
			SYNTAX	INTEGER
			MAX-ACCESS	read-only
			STATUS	current
			::= { hmWanMbusEF 19 }

hmWanMbusEFVIF07		OBJECT-TYPE
			SYNTAX	INTEGER
			MAX-ACCESS	read-only
			STATUS	current
			::= { hmWanMbusEF 20 }

hmWanMbusEFValue07		OBJECT-TYPE
			SYNTAX	INTEGER
			MAX-ACCESS	read-only
			STATUS	current
			::= { hmWanMbusEF 21 }

hmWanMbusEFVIF08		OBJECT-TYPE
			SYNTAX	INTEGER
			MAX-ACCESS	read-only
			STATUS	current
			::= { hmWanMbusEF 22 }

hmWanMbusEFValue08		OBJECT-TYPE
			SYNTAX	INTEGER
			MAX-ACCESS	read-only
			STATUS	current
			::= { hmWanMbusEF 23 }

hmWanMbusEFVIF09		OBJECT-TYPE
			SYNTAX	INTEGER
			MAX-ACCESS	read-only
			STATUS	current
			::= { hmWanMbusEF 24 }

hmWanMbusEFValue09		OBJECT-TYPE
			SYNTAX	INTEGER
			MAX-ACCESS	read-only
			STATUS	current
			::= { hmWanMbusEF 25 }

hmWanMbusEFVIF0A		OBJECT-TYPE
			SYNTAX	INTEGER
			MAX-ACCESS	read-only
			STATUS	current
			::= { hmWanMbusEF 26 }

hmWanMbusEFValue0A		OBJECT-TYPE
			SYNTAX	INTEGER
			MAX-ACCESS	read-only
			STATUS	current
			::= { hmWanMbusEF 27 }

hmWanMbusEFVIF0B		OBJECT-TYPE
			SYNTAX	INTEGER
			MAX-ACCESS	read-only
			STATUS	current
			::= { hmWanMbusEF 28 }

hmWanMbusEFValue0B		OBJECT-TYPE
			SYNTAX	INTEGER
			MAX-ACCESS	read-only
			STATUS	current
			::= { hmWanMbusEF 29 }

hmWanMbusEFVIF0C		OBJECT-TYPE
			SYNTAX	INTEGER
			MAX-ACCESS	read-only
			STATUS	current
			::= { hmWanMbusEF 30 }

hmWanMbusEFValue0C		OBJECT-TYPE
			SYNTAX	INTEGER
			MAX-ACCESS	read-only
			STATUS	current
			::= { hmWanMbusEF 31 }

hmWanMbusEFVIF0D		OBJECT-TYPE
			SYNTAX	INTEGER
			MAX-ACCESS	read-only
			STATUS	current
			::= { hmWanMbusEF 32 }

hmWanMbusEFValue0D		OBJECT-TYPE
			SYNTAX	INTEGER
			MAX-ACCESS	read-only
			STATUS	current
			::= { hmWanMbusEF 33 }

hmWanMbusEFVIF0E		OBJECT-TYPE
			SYNTAX	INTEGER
			MAX-ACCESS	read-only
			STATUS	current
			::= { hmWanMbusEF 34 }

hmWanMbusEFValue0E		OBJECT-TYPE
			SYNTAX	INTEGER
			MAX-ACCESS	read-only
			STATUS	current
			::= { hmWanMbusEF 35 }

hmWanMbusEFVIF0F		OBJECT-TYPE
			SYNTAX	INTEGER
			MAX-ACCESS	read-only
			STATUS	current
			::= { hmWanMbusEF 36 }

hmWanMbusEFValue0F		OBJECT-TYPE
			SYNTAX	INTEGER
			MAX-ACCESS	read-only
			STATUS	current
			::= { hmWanMbusEF 37 }

hmWanMbusEFVIF10		OBJECT-TYPE
			SYNTAX	INTEGER
			MAX-ACCESS	read-only
			STATUS	current
			::= { hmWanMbusEF 38 }

hmWanMbusEFValue10		OBJECT-TYPE
			SYNTAX	INTEGER
			MAX-ACCESS	read-only
			STATUS	current
			::= { hmWanMbusEF 39 }

hmWanMbusEFVIF11		OBJECT-TYPE
			SYNTAX	INTEGER
			MAX-ACCESS	read-only
			STATUS	current
			::= { hmWanMbusEF 40 }

hmWanMbusEFValue11		OBJECT-TYPE
			SYNTAX	INTEGER
			MAX-ACCESS	read-only
			STATUS	current
			::= { hmWanMbusEF 41 }

hmWanMbusEFVIF12		OBJECT-TYPE
			SYNTAX	INTEGER
			MAX-ACCESS	read-only
			STATUS	current
			::= { hmWanMbusEF 42 }

hmWanMbusEFValue12		OBJECT-TYPE
			SYNTAX	INTEGER
			MAX-ACCESS	read-only
			STATUS	current
			::= { hmWanMbusEF 43 }

hmWanMbusEFVIF13		OBJECT-TYPE
			SYNTAX	INTEGER
			MAX-ACCESS	read-only
			STATUS	current
			::= { hmWanMbusEF 44 }

hmWanMbusEFValue13		OBJECT-TYPE
			SYNTAX	INTEGER
			MAX-ACCESS	read-only
			STATUS	current
			::= { hmWanMbusEF 45 }

hmWanMbusEFVIF14		OBJECT-TYPE
			SYNTAX	INTEGER
			MAX-ACCESS	read-only
			STATUS	current
			::= { hmWanMbusEF 46 }

hmWanMbusEFValue14		OBJECT-TYPE
			SYNTAX	INTEGER
			MAX-ACCESS	read-only
			STATUS	current
			::= { hmWanMbusEF 47 }

hmWanMbusEFVIF15		OBJECT-TYPE
			SYNTAX	INTEGER
			MAX-ACCESS	read-only
			STATUS	current
			::= { hmWanMbusEF 48 }

hmWanMbusEFValue15		OBJECT-TYPE
			SYNTAX	INTEGER
			MAX-ACCESS	read-only
			STATUS	current
			::= { hmWanMbusEF 49 }

hmWanMbusEFVIF16		OBJECT-TYPE
			SYNTAX	INTEGER
			MAX-ACCESS	read-only
			STATUS	current
			::= { hmWanMbusEF 50 }

hmWanMbusEFValue16		OBJECT-TYPE
			SYNTAX	INTEGER
			MAX-ACCESS	read-only
			STATUS	current
			::= { hmWanMbusEF 51 }

hmWanMbusEFVIF17		OBJECT-TYPE
			SYNTAX	INTEGER
			MAX-ACCESS	read-only
			STATUS	current
			::= { hmWanMbusEF 52 }

hmWanMbusEFValue17		OBJECT-TYPE
			SYNTAX	INTEGER
			MAX-ACCESS	read-only
			STATUS	current
			::= { hmWanMbusEF 53 }

hmWanMbusEFVIF18		OBJECT-TYPE
			SYNTAX	INTEGER
			MAX-ACCESS	read-only
			STATUS	current
			::= { hmWanMbusEF 54 }

hmWanMbusEFValue18		OBJECT-TYPE
			SYNTAX	INTEGER
			MAX-ACCESS	read-only
			STATUS	current
			::= { hmWanMbusEF 55 }

hmWanMbusEFVIF19		OBJECT-TYPE
			SYNTAX	INTEGER
			MAX-ACCESS	read-only
			STATUS	current
			::= { hmWanMbusEF 56 }

hmWanMbusEFValue19		OBJECT-TYPE
			SYNTAX	INTEGER
			MAX-ACCESS	read-only
			STATUS	current
			::= { hmWanMbusEF 57 }

hmWanMbusEFVIF1A		OBJECT-TYPE
			SYNTAX	INTEGER
			MAX-ACCESS	read-only
			STATUS	current
			::= { hmWanMbusEF 58 }

hmWanMbusEFValue1A		OBJECT-TYPE
			SYNTAX	INTEGER
			MAX-ACCESS	read-only
			STATUS	current
			::= { hmWanMbusEF 59 }

hmWanMbusEFVIF1B		OBJECT-TYPE
			SYNTAX	INTEGER
			MAX-ACCESS	read-only
			STATUS	current
			::= { hmWanMbusEF 60 }

hmWanMbusEFValue1B		OBJECT-TYPE
			SYNTAX	INTEGER
			MAX-ACCESS	read-only
			STATUS	current
			::= { hmWanMbusEF 61 }

hmWanMbusEFVIF1C		OBJECT-TYPE
			SYNTAX	INTEGER
			MAX-ACCESS	read-only
			STATUS	current
			::= { hmWanMbusEF 62 }

hmWanMbusEFValue1C		OBJECT-TYPE
			SYNTAX	INTEGER
			MAX-ACCESS	read-only
			STATUS	current
			::= { hmWanMbusEF 63 }

hmWanMbusEFVIF1D		OBJECT-TYPE
			SYNTAX	INTEGER
			MAX-ACCESS	read-only
			STATUS	current
			::= { hmWanMbusEF 64 }

hmWanMbusEFValue1D		OBJECT-TYPE
			SYNTAX	INTEGER
			MAX-ACCESS	read-only
			STATUS	current
			::= { hmWanMbusEF 65 }

hmWanMbusEFVIF1E		OBJECT-TYPE
			SYNTAX	INTEGER
			MAX-ACCESS	read-only
			STATUS	current
			::= { hmWanMbusEF 66 }

hmWanMbusEFValue1E		OBJECT-TYPE
			SYNTAX	INTEGER
			MAX-ACCESS	read-only
			STATUS	current
			::= { hmWanMbusEF 67 }

hmWanMbusEFVIF1F		OBJECT-TYPE
			SYNTAX	INTEGER
			MAX-ACCESS	read-only
			STATUS	current
			::= { hmWanMbusEF 68 }

hmWanMbusEFValue1F		OBJECT-TYPE
			SYNTAX	INTEGER
			MAX-ACCESS	read-only
			STATUS	current
			::= { hmWanMbusEF 69 }

hmWanMbusEFVIF20		OBJECT-TYPE
			SYNTAX	INTEGER
			MAX-ACCESS	read-only
			STATUS	current
			::= { hmWanMbusEF 70 }

hmWanMbusEFValue20		OBJECT-TYPE
			SYNTAX	INTEGER
			MAX-ACCESS	read-only
			STATUS	current
			::= { hmWanMbusEF 71 }

hmWanMbusEFVIF21		OBJECT-TYPE
			SYNTAX	INTEGER
			MAX-ACCESS	read-only
			STATUS	current
			::= { hmWanMbusEF 72 }

hmWanMbusEFValue21		OBJECT-TYPE
			SYNTAX	INTEGER
			MAX-ACCESS	read-only
			STATUS	current
			::= { hmWanMbusEF 73 }

hmWanMbusEFVIF22		OBJECT-TYPE
			SYNTAX	INTEGER
			MAX-ACCESS	read-only
			STATUS	current
			::= { hmWanMbusEF 74 }

hmWanMbusEFValue22		OBJECT-TYPE
			SYNTAX	INTEGER
			MAX-ACCESS	read-only
			STATUS	current
			::= { hmWanMbusEF 75 }

hmWanMbusEFVIF23		OBJECT-TYPE
			SYNTAX	INTEGER
			MAX-ACCESS	read-only
			STATUS	current
			::= { hmWanMbusEF 76 }

hmWanMbusEFValue23		OBJECT-TYPE
			SYNTAX	INTEGER
			MAX-ACCESS	read-only
			STATUS	current
			::= { hmWanMbusEF 77 }

hmWanMbusEFVIF24		OBJECT-TYPE
			SYNTAX	INTEGER
			MAX-ACCESS	read-only
			STATUS	current
			::= { hmWanMbusEF 78 }

hmWanMbusEFValue24		OBJECT-TYPE
			SYNTAX	INTEGER
			MAX-ACCESS	read-only
			STATUS	current
			::= { hmWanMbusEF 79 }

hmWanMbusEFVIF25		OBJECT-TYPE
			SYNTAX	INTEGER
			MAX-ACCESS	read-only
			STATUS	current
			::= { hmWanMbusEF 80 }

hmWanMbusEFValue25		OBJECT-TYPE
			SYNTAX	INTEGER
			MAX-ACCESS	read-only
			STATUS	current
			::= { hmWanMbusEF 81 }

hmWanMbusEFVIF26		OBJECT-TYPE
			SYNTAX	INTEGER
			MAX-ACCESS	read-only
			STATUS	current
			::= { hmWanMbusEF 82 }

hmWanMbusEFValue26		OBJECT-TYPE
			SYNTAX	INTEGER
			MAX-ACCESS	read-only
			STATUS	current
			::= { hmWanMbusEF 83 }

hmWanMbusEFVIF27		OBJECT-TYPE
			SYNTAX	INTEGER
			MAX-ACCESS	read-only
			STATUS	current
			::= { hmWanMbusEF 84 }

hmWanMbusEFValue27		OBJECT-TYPE
			SYNTAX	INTEGER
			MAX-ACCESS	read-only
			STATUS	current
			::= { hmWanMbusEF 85 }

hmWanMbusEFVIF28		OBJECT-TYPE
			SYNTAX	INTEGER
			MAX-ACCESS	read-only
			STATUS	current
			::= { hmWanMbusEF 86 }

hmWanMbusEFValue28		OBJECT-TYPE
			SYNTAX	INTEGER
			MAX-ACCESS	read-only
			STATUS	current
			::= { hmWanMbusEF 87 }

hmWanMbusEFVIF29		OBJECT-TYPE
			SYNTAX	INTEGER
			MAX-ACCESS	read-only
			STATUS	current
			::= { hmWanMbusEF 88 }

hmWanMbusEFValue29		OBJECT-TYPE
			SYNTAX	INTEGER
			MAX-ACCESS	read-only
			STATUS	current
			::= { hmWanMbusEF 89 }

hmWanMbusEFVIF2A		OBJECT-TYPE
			SYNTAX	INTEGER
			MAX-ACCESS	read-only
			STATUS	current
			::= { hmWanMbusEF 90 }

hmWanMbusEFValue2A		OBJECT-TYPE
			SYNTAX	INTEGER
			MAX-ACCESS	read-only
			STATUS	current
			::= { hmWanMbusEF 91 }

hmWanMbusEFVIF2B		OBJECT-TYPE
			SYNTAX	INTEGER
			MAX-ACCESS	read-only
			STATUS	current
			::= { hmWanMbusEF 92 }

hmWanMbusEFValue2B		OBJECT-TYPE
			SYNTAX	INTEGER
			MAX-ACCESS	read-only
			STATUS	current
			::= { hmWanMbusEF 93 }

hmWanMbusEFVIF2C		OBJECT-TYPE
			SYNTAX	INTEGER
			MAX-ACCESS	read-only
			STATUS	current
			::= { hmWanMbusEF 94 }

hmWanMbusEFValue2C		OBJECT-TYPE
			SYNTAX	INTEGER
			MAX-ACCESS	read-only
			STATUS	current
			::= { hmWanMbusEF 95 }

hmWanMbusEFVIF2D		OBJECT-TYPE
			SYNTAX	INTEGER
			MAX-ACCESS	read-only
			STATUS	current
			::= { hmWanMbusEF 96 }

hmWanMbusEFValue2D		OBJECT-TYPE
			SYNTAX	INTEGER
			MAX-ACCESS	read-only
			STATUS	current
			::= { hmWanMbusEF 97 }

hmWanMbusEFVIF2E		OBJECT-TYPE
			SYNTAX	INTEGER
			MAX-ACCESS	read-only
			STATUS	current
			::= { hmWanMbusEF 98 }

hmWanMbusEFValue2E		OBJECT-TYPE
			SYNTAX	INTEGER
			MAX-ACCESS	read-only
			STATUS	current
			::= { hmWanMbusEF 99 }

hmWanMbusEFVIF2F		OBJECT-TYPE
			SYNTAX	INTEGER
			MAX-ACCESS	read-only
			STATUS	current
			::= { hmWanMbusEF 100 }

hmWanMbusEFValue2F		OBJECT-TYPE
			SYNTAX	INTEGER
			MAX-ACCESS	read-only
			STATUS	current
			::= { hmWanMbusEF 101 }

hmWanMbusF0			OBJECT IDENTIFIER ::= { hmWanMbus 240 }

hmWanMbusF0IdNumber		OBJECT-TYPE
			SYNTAX	Gauge32
			MAX-ACCESS	read-only
			STATUS	current
			::= { hmWanMbusF0 1 }

hmWanMbusF0Manufacturer	OBJECT-TYPE
			SYNTAX	Gauge32
			MAX-ACCESS	read-only
			STATUS	current
			::= { hmWanMbusF0 2 }

hmWanMbusF0Version		OBJECT-TYPE
			SYNTAX	Gauge32
			MAX-ACCESS	read-only
			STATUS	current
			::= { hmWanMbusF0 3 }

hmWanMbusF0Medium		OBJECT-TYPE
			SYNTAX	Gauge32
			MAX-ACCESS	read-only
			STATUS	current
			::= { hmWanMbusF0 4 }

hmWanMbusF0Status		OBJECT-TYPE
			SYNTAX	Gauge32
			MAX-ACCESS	read-only
			STATUS	current
			::= { hmWanMbusF0 5 }

hmWanMbusF0VIF00		OBJECT-TYPE
			SYNTAX	INTEGER
			MAX-ACCESS	read-only
			STATUS	current
			::= { hmWanMbusF0 6 }

hmWanMbusF0Value00		OBJECT-TYPE
			SYNTAX	INTEGER
			MAX-ACCESS	read-only
			STATUS	current
			::= { hmWanMbusF0 7 }

hmWanMbusF0VIF01		OBJECT-TYPE
			SYNTAX	INTEGER
			MAX-ACCESS	read-only
			STATUS	current
			::= { hmWanMbusF0 8 }

hmWanMbusF0Value01		OBJECT-TYPE
			SYNTAX	INTEGER
			MAX-ACCESS	read-only
			STATUS	current
			::= { hmWanMbusF0 9 }

hmWanMbusF0VIF02		OBJECT-TYPE
			SYNTAX	INTEGER
			MAX-ACCESS	read-only
			STATUS	current
			::= { hmWanMbusF0 10 }

hmWanMbusF0Value02		OBJECT-TYPE
			SYNTAX	INTEGER
			MAX-ACCESS	read-only
			STATUS	current
			::= { hmWanMbusF0 11 }

hmWanMbusF0VIF03		OBJECT-TYPE
			SYNTAX	INTEGER
			MAX-ACCESS	read-only
			STATUS	current
			::= { hmWanMbusF0 12 }

hmWanMbusF0Value03		OBJECT-TYPE
			SYNTAX	INTEGER
			MAX-ACCESS	read-only
			STATUS	current
			::= { hmWanMbusF0 13 }

hmWanMbusF0VIF04		OBJECT-TYPE
			SYNTAX	INTEGER
			MAX-ACCESS	read-only
			STATUS	current
			::= { hmWanMbusF0 14 }

hmWanMbusF0Value04		OBJECT-TYPE
			SYNTAX	INTEGER
			MAX-ACCESS	read-only
			STATUS	current
			::= { hmWanMbusF0 15 }

hmWanMbusF0VIF05		OBJECT-TYPE
			SYNTAX	INTEGER
			MAX-ACCESS	read-only
			STATUS	current
			::= { hmWanMbusF0 16 }

hmWanMbusF0Value05		OBJECT-TYPE
			SYNTAX	INTEGER
			MAX-ACCESS	read-only
			STATUS	current
			::= { hmWanMbusF0 17 }

hmWanMbusF0VIF06		OBJECT-TYPE
			SYNTAX	INTEGER
			MAX-ACCESS	read-only
			STATUS	current
			::= { hmWanMbusF0 18 }

hmWanMbusF0Value06		OBJECT-TYPE
			SYNTAX	INTEGER
			MAX-ACCESS	read-only
			STATUS	current
			::= { hmWanMbusF0 19 }

hmWanMbusF0VIF07		OBJECT-TYPE
			SYNTAX	INTEGER
			MAX-ACCESS	read-only
			STATUS	current
			::= { hmWanMbusF0 20 }

hmWanMbusF0Value07		OBJECT-TYPE
			SYNTAX	INTEGER
			MAX-ACCESS	read-only
			STATUS	current
			::= { hmWanMbusF0 21 }

hmWanMbusF0VIF08		OBJECT-TYPE
			SYNTAX	INTEGER
			MAX-ACCESS	read-only
			STATUS	current
			::= { hmWanMbusF0 22 }

hmWanMbusF0Value08		OBJECT-TYPE
			SYNTAX	INTEGER
			MAX-ACCESS	read-only
			STATUS	current
			::= { hmWanMbusF0 23 }

hmWanMbusF0VIF09		OBJECT-TYPE
			SYNTAX	INTEGER
			MAX-ACCESS	read-only
			STATUS	current
			::= { hmWanMbusF0 24 }

hmWanMbusF0Value09		OBJECT-TYPE
			SYNTAX	INTEGER
			MAX-ACCESS	read-only
			STATUS	current
			::= { hmWanMbusF0 25 }

hmWanMbusF0VIF0A		OBJECT-TYPE
			SYNTAX	INTEGER
			MAX-ACCESS	read-only
			STATUS	current
			::= { hmWanMbusF0 26 }

hmWanMbusF0Value0A		OBJECT-TYPE
			SYNTAX	INTEGER
			MAX-ACCESS	read-only
			STATUS	current
			::= { hmWanMbusF0 27 }

hmWanMbusF0VIF0B		OBJECT-TYPE
			SYNTAX	INTEGER
			MAX-ACCESS	read-only
			STATUS	current
			::= { hmWanMbusF0 28 }

hmWanMbusF0Value0B		OBJECT-TYPE
			SYNTAX	INTEGER
			MAX-ACCESS	read-only
			STATUS	current
			::= { hmWanMbusF0 29 }

hmWanMbusF0VIF0C		OBJECT-TYPE
			SYNTAX	INTEGER
			MAX-ACCESS	read-only
			STATUS	current
			::= { hmWanMbusF0 30 }

hmWanMbusF0Value0C		OBJECT-TYPE
			SYNTAX	INTEGER
			MAX-ACCESS	read-only
			STATUS	current
			::= { hmWanMbusF0 31 }

hmWanMbusF0VIF0D		OBJECT-TYPE
			SYNTAX	INTEGER
			MAX-ACCESS	read-only
			STATUS	current
			::= { hmWanMbusF0 32 }

hmWanMbusF0Value0D		OBJECT-TYPE
			SYNTAX	INTEGER
			MAX-ACCESS	read-only
			STATUS	current
			::= { hmWanMbusF0 33 }

hmWanMbusF0VIF0E		OBJECT-TYPE
			SYNTAX	INTEGER
			MAX-ACCESS	read-only
			STATUS	current
			::= { hmWanMbusF0 34 }

hmWanMbusF0Value0E		OBJECT-TYPE
			SYNTAX	INTEGER
			MAX-ACCESS	read-only
			STATUS	current
			::= { hmWanMbusF0 35 }

hmWanMbusF0VIF0F		OBJECT-TYPE
			SYNTAX	INTEGER
			MAX-ACCESS	read-only
			STATUS	current
			::= { hmWanMbusF0 36 }

hmWanMbusF0Value0F		OBJECT-TYPE
			SYNTAX	INTEGER
			MAX-ACCESS	read-only
			STATUS	current
			::= { hmWanMbusF0 37 }

hmWanMbusF0VIF10		OBJECT-TYPE
			SYNTAX	INTEGER
			MAX-ACCESS	read-only
			STATUS	current
			::= { hmWanMbusF0 38 }

hmWanMbusF0Value10		OBJECT-TYPE
			SYNTAX	INTEGER
			MAX-ACCESS	read-only
			STATUS	current
			::= { hmWanMbusF0 39 }

hmWanMbusF0VIF11		OBJECT-TYPE
			SYNTAX	INTEGER
			MAX-ACCESS	read-only
			STATUS	current
			::= { hmWanMbusF0 40 }

hmWanMbusF0Value11		OBJECT-TYPE
			SYNTAX	INTEGER
			MAX-ACCESS	read-only
			STATUS	current
			::= { hmWanMbusF0 41 }

hmWanMbusF0VIF12		OBJECT-TYPE
			SYNTAX	INTEGER
			MAX-ACCESS	read-only
			STATUS	current
			::= { hmWanMbusF0 42 }

hmWanMbusF0Value12		OBJECT-TYPE
			SYNTAX	INTEGER
			MAX-ACCESS	read-only
			STATUS	current
			::= { hmWanMbusF0 43 }

hmWanMbusF0VIF13		OBJECT-TYPE
			SYNTAX	INTEGER
			MAX-ACCESS	read-only
			STATUS	current
			::= { hmWanMbusF0 44 }

hmWanMbusF0Value13		OBJECT-TYPE
			SYNTAX	INTEGER
			MAX-ACCESS	read-only
			STATUS	current
			::= { hmWanMbusF0 45 }

hmWanMbusF0VIF14		OBJECT-TYPE
			SYNTAX	INTEGER
			MAX-ACCESS	read-only
			STATUS	current
			::= { hmWanMbusF0 46 }

hmWanMbusF0Value14		OBJECT-TYPE
			SYNTAX	INTEGER
			MAX-ACCESS	read-only
			STATUS	current
			::= { hmWanMbusF0 47 }

hmWanMbusF0VIF15		OBJECT-TYPE
			SYNTAX	INTEGER
			MAX-ACCESS	read-only
			STATUS	current
			::= { hmWanMbusF0 48 }

hmWanMbusF0Value15		OBJECT-TYPE
			SYNTAX	INTEGER
			MAX-ACCESS	read-only
			STATUS	current
			::= { hmWanMbusF0 49 }

hmWanMbusF0VIF16		OBJECT-TYPE
			SYNTAX	INTEGER
			MAX-ACCESS	read-only
			STATUS	current
			::= { hmWanMbusF0 50 }

hmWanMbusF0Value16		OBJECT-TYPE
			SYNTAX	INTEGER
			MAX-ACCESS	read-only
			STATUS	current
			::= { hmWanMbusF0 51 }

hmWanMbusF0VIF17		OBJECT-TYPE
			SYNTAX	INTEGER
			MAX-ACCESS	read-only
			STATUS	current
			::= { hmWanMbusF0 52 }

hmWanMbusF0Value17		OBJECT-TYPE
			SYNTAX	INTEGER
			MAX-ACCESS	read-only
			STATUS	current
			::= { hmWanMbusF0 53 }

hmWanMbusF0VIF18		OBJECT-TYPE
			SYNTAX	INTEGER
			MAX-ACCESS	read-only
			STATUS	current
			::= { hmWanMbusF0 54 }

hmWanMbusF0Value18		OBJECT-TYPE
			SYNTAX	INTEGER
			MAX-ACCESS	read-only
			STATUS	current
			::= { hmWanMbusF0 55 }

hmWanMbusF0VIF19		OBJECT-TYPE
			SYNTAX	INTEGER
			MAX-ACCESS	read-only
			STATUS	current
			::= { hmWanMbusF0 56 }

hmWanMbusF0Value19		OBJECT-TYPE
			SYNTAX	INTEGER
			MAX-ACCESS	read-only
			STATUS	current
			::= { hmWanMbusF0 57 }

hmWanMbusF0VIF1A		OBJECT-TYPE
			SYNTAX	INTEGER
			MAX-ACCESS	read-only
			STATUS	current
			::= { hmWanMbusF0 58 }

hmWanMbusF0Value1A		OBJECT-TYPE
			SYNTAX	INTEGER
			MAX-ACCESS	read-only
			STATUS	current
			::= { hmWanMbusF0 59 }

hmWanMbusF0VIF1B		OBJECT-TYPE
			SYNTAX	INTEGER
			MAX-ACCESS	read-only
			STATUS	current
			::= { hmWanMbusF0 60 }

hmWanMbusF0Value1B		OBJECT-TYPE
			SYNTAX	INTEGER
			MAX-ACCESS	read-only
			STATUS	current
			::= { hmWanMbusF0 61 }

hmWanMbusF0VIF1C		OBJECT-TYPE
			SYNTAX	INTEGER
			MAX-ACCESS	read-only
			STATUS	current
			::= { hmWanMbusF0 62 }

hmWanMbusF0Value1C		OBJECT-TYPE
			SYNTAX	INTEGER
			MAX-ACCESS	read-only
			STATUS	current
			::= { hmWanMbusF0 63 }

hmWanMbusF0VIF1D		OBJECT-TYPE
			SYNTAX	INTEGER
			MAX-ACCESS	read-only
			STATUS	current
			::= { hmWanMbusF0 64 }

hmWanMbusF0Value1D		OBJECT-TYPE
			SYNTAX	INTEGER
			MAX-ACCESS	read-only
			STATUS	current
			::= { hmWanMbusF0 65 }

hmWanMbusF0VIF1E		OBJECT-TYPE
			SYNTAX	INTEGER
			MAX-ACCESS	read-only
			STATUS	current
			::= { hmWanMbusF0 66 }

hmWanMbusF0Value1E		OBJECT-TYPE
			SYNTAX	INTEGER
			MAX-ACCESS	read-only
			STATUS	current
			::= { hmWanMbusF0 67 }

hmWanMbusF0VIF1F		OBJECT-TYPE
			SYNTAX	INTEGER
			MAX-ACCESS	read-only
			STATUS	current
			::= { hmWanMbusF0 68 }

hmWanMbusF0Value1F		OBJECT-TYPE
			SYNTAX	INTEGER
			MAX-ACCESS	read-only
			STATUS	current
			::= { hmWanMbusF0 69 }

hmWanMbusF0VIF20		OBJECT-TYPE
			SYNTAX	INTEGER
			MAX-ACCESS	read-only
			STATUS	current
			::= { hmWanMbusF0 70 }

hmWanMbusF0Value20		OBJECT-TYPE
			SYNTAX	INTEGER
			MAX-ACCESS	read-only
			STATUS	current
			::= { hmWanMbusF0 71 }

hmWanMbusF0VIF21		OBJECT-TYPE
			SYNTAX	INTEGER
			MAX-ACCESS	read-only
			STATUS	current
			::= { hmWanMbusF0 72 }

hmWanMbusF0Value21		OBJECT-TYPE
			SYNTAX	INTEGER
			MAX-ACCESS	read-only
			STATUS	current
			::= { hmWanMbusF0 73 }

hmWanMbusF0VIF22		OBJECT-TYPE
			SYNTAX	INTEGER
			MAX-ACCESS	read-only
			STATUS	current
			::= { hmWanMbusF0 74 }

hmWanMbusF0Value22		OBJECT-TYPE
			SYNTAX	INTEGER
			MAX-ACCESS	read-only
			STATUS	current
			::= { hmWanMbusF0 75 }

hmWanMbusF0VIF23		OBJECT-TYPE
			SYNTAX	INTEGER
			MAX-ACCESS	read-only
			STATUS	current
			::= { hmWanMbusF0 76 }

hmWanMbusF0Value23		OBJECT-TYPE
			SYNTAX	INTEGER
			MAX-ACCESS	read-only
			STATUS	current
			::= { hmWanMbusF0 77 }

hmWanMbusF0VIF24		OBJECT-TYPE
			SYNTAX	INTEGER
			MAX-ACCESS	read-only
			STATUS	current
			::= { hmWanMbusF0 78 }

hmWanMbusF0Value24		OBJECT-TYPE
			SYNTAX	INTEGER
			MAX-ACCESS	read-only
			STATUS	current
			::= { hmWanMbusF0 79 }

hmWanMbusF0VIF25		OBJECT-TYPE
			SYNTAX	INTEGER
			MAX-ACCESS	read-only
			STATUS	current
			::= { hmWanMbusF0 80 }

hmWanMbusF0Value25		OBJECT-TYPE
			SYNTAX	INTEGER
			MAX-ACCESS	read-only
			STATUS	current
			::= { hmWanMbusF0 81 }

hmWanMbusF0VIF26		OBJECT-TYPE
			SYNTAX	INTEGER
			MAX-ACCESS	read-only
			STATUS	current
			::= { hmWanMbusF0 82 }

hmWanMbusF0Value26		OBJECT-TYPE
			SYNTAX	INTEGER
			MAX-ACCESS	read-only
			STATUS	current
			::= { hmWanMbusF0 83 }

hmWanMbusF0VIF27		OBJECT-TYPE
			SYNTAX	INTEGER
			MAX-ACCESS	read-only
			STATUS	current
			::= { hmWanMbusF0 84 }

hmWanMbusF0Value27		OBJECT-TYPE
			SYNTAX	INTEGER
			MAX-ACCESS	read-only
			STATUS	current
			::= { hmWanMbusF0 85 }

hmWanMbusF0VIF28		OBJECT-TYPE
			SYNTAX	INTEGER
			MAX-ACCESS	read-only
			STATUS	current
			::= { hmWanMbusF0 86 }

hmWanMbusF0Value28		OBJECT-TYPE
			SYNTAX	INTEGER
			MAX-ACCESS	read-only
			STATUS	current
			::= { hmWanMbusF0 87 }

hmWanMbusF0VIF29		OBJECT-TYPE
			SYNTAX	INTEGER
			MAX-ACCESS	read-only
			STATUS	current
			::= { hmWanMbusF0 88 }

hmWanMbusF0Value29		OBJECT-TYPE
			SYNTAX	INTEGER
			MAX-ACCESS	read-only
			STATUS	current
			::= { hmWanMbusF0 89 }

hmWanMbusF0VIF2A		OBJECT-TYPE
			SYNTAX	INTEGER
			MAX-ACCESS	read-only
			STATUS	current
			::= { hmWanMbusF0 90 }

hmWanMbusF0Value2A		OBJECT-TYPE
			SYNTAX	INTEGER
			MAX-ACCESS	read-only
			STATUS	current
			::= { hmWanMbusF0 91 }

hmWanMbusF0VIF2B		OBJECT-TYPE
			SYNTAX	INTEGER
			MAX-ACCESS	read-only
			STATUS	current
			::= { hmWanMbusF0 92 }

hmWanMbusF0Value2B		OBJECT-TYPE
			SYNTAX	INTEGER
			MAX-ACCESS	read-only
			STATUS	current
			::= { hmWanMbusF0 93 }

hmWanMbusF0VIF2C		OBJECT-TYPE
			SYNTAX	INTEGER
			MAX-ACCESS	read-only
			STATUS	current
			::= { hmWanMbusF0 94 }

hmWanMbusF0Value2C		OBJECT-TYPE
			SYNTAX	INTEGER
			MAX-ACCESS	read-only
			STATUS	current
			::= { hmWanMbusF0 95 }

hmWanMbusF0VIF2D		OBJECT-TYPE
			SYNTAX	INTEGER
			MAX-ACCESS	read-only
			STATUS	current
			::= { hmWanMbusF0 96 }

hmWanMbusF0Value2D		OBJECT-TYPE
			SYNTAX	INTEGER
			MAX-ACCESS	read-only
			STATUS	current
			::= { hmWanMbusF0 97 }

hmWanMbusF0VIF2E		OBJECT-TYPE
			SYNTAX	INTEGER
			MAX-ACCESS	read-only
			STATUS	current
			::= { hmWanMbusF0 98 }

hmWanMbusF0Value2E		OBJECT-TYPE
			SYNTAX	INTEGER
			MAX-ACCESS	read-only
			STATUS	current
			::= { hmWanMbusF0 99 }

hmWanMbusF0VIF2F		OBJECT-TYPE
			SYNTAX	INTEGER
			MAX-ACCESS	read-only
			STATUS	current
			::= { hmWanMbusF0 100 }

hmWanMbusF0Value2F		OBJECT-TYPE
			SYNTAX	INTEGER
			MAX-ACCESS	read-only
			STATUS	current
			::= { hmWanMbusF0 101 }

hmWanMbusF1			OBJECT IDENTIFIER ::= { hmWanMbus 241 }

hmWanMbusF1IdNumber		OBJECT-TYPE
			SYNTAX	Gauge32
			MAX-ACCESS	read-only
			STATUS	current
			::= { hmWanMbusF1 1 }

hmWanMbusF1Manufacturer	OBJECT-TYPE
			SYNTAX	Gauge32
			MAX-ACCESS	read-only
			STATUS	current
			::= { hmWanMbusF1 2 }

hmWanMbusF1Version		OBJECT-TYPE
			SYNTAX	Gauge32
			MAX-ACCESS	read-only
			STATUS	current
			::= { hmWanMbusF1 3 }

hmWanMbusF1Medium		OBJECT-TYPE
			SYNTAX	Gauge32
			MAX-ACCESS	read-only
			STATUS	current
			::= { hmWanMbusF1 4 }

hmWanMbusF1Status		OBJECT-TYPE
			SYNTAX	Gauge32
			MAX-ACCESS	read-only
			STATUS	current
			::= { hmWanMbusF1 5 }

hmWanMbusF1VIF00		OBJECT-TYPE
			SYNTAX	INTEGER
			MAX-ACCESS	read-only
			STATUS	current
			::= { hmWanMbusF1 6 }

hmWanMbusF1Value00		OBJECT-TYPE
			SYNTAX	INTEGER
			MAX-ACCESS	read-only
			STATUS	current
			::= { hmWanMbusF1 7 }

hmWanMbusF1VIF01		OBJECT-TYPE
			SYNTAX	INTEGER
			MAX-ACCESS	read-only
			STATUS	current
			::= { hmWanMbusF1 8 }

hmWanMbusF1Value01		OBJECT-TYPE
			SYNTAX	INTEGER
			MAX-ACCESS	read-only
			STATUS	current
			::= { hmWanMbusF1 9 }

hmWanMbusF1VIF02		OBJECT-TYPE
			SYNTAX	INTEGER
			MAX-ACCESS	read-only
			STATUS	current
			::= { hmWanMbusF1 10 }

hmWanMbusF1Value02		OBJECT-TYPE
			SYNTAX	INTEGER
			MAX-ACCESS	read-only
			STATUS	current
			::= { hmWanMbusF1 11 }

hmWanMbusF1VIF03		OBJECT-TYPE
			SYNTAX	INTEGER
			MAX-ACCESS	read-only
			STATUS	current
			::= { hmWanMbusF1 12 }

hmWanMbusF1Value03		OBJECT-TYPE
			SYNTAX	INTEGER
			MAX-ACCESS	read-only
			STATUS	current
			::= { hmWanMbusF1 13 }

hmWanMbusF1VIF04		OBJECT-TYPE
			SYNTAX	INTEGER
			MAX-ACCESS	read-only
			STATUS	current
			::= { hmWanMbusF1 14 }

hmWanMbusF1Value04		OBJECT-TYPE
			SYNTAX	INTEGER
			MAX-ACCESS	read-only
			STATUS	current
			::= { hmWanMbusF1 15 }

hmWanMbusF1VIF05		OBJECT-TYPE
			SYNTAX	INTEGER
			MAX-ACCESS	read-only
			STATUS	current
			::= { hmWanMbusF1 16 }

hmWanMbusF1Value05		OBJECT-TYPE
			SYNTAX	INTEGER
			MAX-ACCESS	read-only
			STATUS	current
			::= { hmWanMbusF1 17 }

hmWanMbusF1VIF06		OBJECT-TYPE
			SYNTAX	INTEGER
			MAX-ACCESS	read-only
			STATUS	current
			::= { hmWanMbusF1 18 }

hmWanMbusF1Value06		OBJECT-TYPE
			SYNTAX	INTEGER
			MAX-ACCESS	read-only
			STATUS	current
			::= { hmWanMbusF1 19 }

hmWanMbusF1VIF07		OBJECT-TYPE
			SYNTAX	INTEGER
			MAX-ACCESS	read-only
			STATUS	current
			::= { hmWanMbusF1 20 }

hmWanMbusF1Value07		OBJECT-TYPE
			SYNTAX	INTEGER
			MAX-ACCESS	read-only
			STATUS	current
			::= { hmWanMbusF1 21 }

hmWanMbusF1VIF08		OBJECT-TYPE
			SYNTAX	INTEGER
			MAX-ACCESS	read-only
			STATUS	current
			::= { hmWanMbusF1 22 }

hmWanMbusF1Value08		OBJECT-TYPE
			SYNTAX	INTEGER
			MAX-ACCESS	read-only
			STATUS	current
			::= { hmWanMbusF1 23 }

hmWanMbusF1VIF09		OBJECT-TYPE
			SYNTAX	INTEGER
			MAX-ACCESS	read-only
			STATUS	current
			::= { hmWanMbusF1 24 }

hmWanMbusF1Value09		OBJECT-TYPE
			SYNTAX	INTEGER
			MAX-ACCESS	read-only
			STATUS	current
			::= { hmWanMbusF1 25 }

hmWanMbusF1VIF0A		OBJECT-TYPE
			SYNTAX	INTEGER
			MAX-ACCESS	read-only
			STATUS	current
			::= { hmWanMbusF1 26 }

hmWanMbusF1Value0A		OBJECT-TYPE
			SYNTAX	INTEGER
			MAX-ACCESS	read-only
			STATUS	current
			::= { hmWanMbusF1 27 }

hmWanMbusF1VIF0B		OBJECT-TYPE
			SYNTAX	INTEGER
			MAX-ACCESS	read-only
			STATUS	current
			::= { hmWanMbusF1 28 }

hmWanMbusF1Value0B		OBJECT-TYPE
			SYNTAX	INTEGER
			MAX-ACCESS	read-only
			STATUS	current
			::= { hmWanMbusF1 29 }

hmWanMbusF1VIF0C		OBJECT-TYPE
			SYNTAX	INTEGER
			MAX-ACCESS	read-only
			STATUS	current
			::= { hmWanMbusF1 30 }

hmWanMbusF1Value0C		OBJECT-TYPE
			SYNTAX	INTEGER
			MAX-ACCESS	read-only
			STATUS	current
			::= { hmWanMbusF1 31 }

hmWanMbusF1VIF0D		OBJECT-TYPE
			SYNTAX	INTEGER
			MAX-ACCESS	read-only
			STATUS	current
			::= { hmWanMbusF1 32 }

hmWanMbusF1Value0D		OBJECT-TYPE
			SYNTAX	INTEGER
			MAX-ACCESS	read-only
			STATUS	current
			::= { hmWanMbusF1 33 }

hmWanMbusF1VIF0E		OBJECT-TYPE
			SYNTAX	INTEGER
			MAX-ACCESS	read-only
			STATUS	current
			::= { hmWanMbusF1 34 }

hmWanMbusF1Value0E		OBJECT-TYPE
			SYNTAX	INTEGER
			MAX-ACCESS	read-only
			STATUS	current
			::= { hmWanMbusF1 35 }

hmWanMbusF1VIF0F		OBJECT-TYPE
			SYNTAX	INTEGER
			MAX-ACCESS	read-only
			STATUS	current
			::= { hmWanMbusF1 36 }

hmWanMbusF1Value0F		OBJECT-TYPE
			SYNTAX	INTEGER
			MAX-ACCESS	read-only
			STATUS	current
			::= { hmWanMbusF1 37 }

hmWanMbusF1VIF10		OBJECT-TYPE
			SYNTAX	INTEGER
			MAX-ACCESS	read-only
			STATUS	current
			::= { hmWanMbusF1 38 }

hmWanMbusF1Value10		OBJECT-TYPE
			SYNTAX	INTEGER
			MAX-ACCESS	read-only
			STATUS	current
			::= { hmWanMbusF1 39 }

hmWanMbusF1VIF11		OBJECT-TYPE
			SYNTAX	INTEGER
			MAX-ACCESS	read-only
			STATUS	current
			::= { hmWanMbusF1 40 }

hmWanMbusF1Value11		OBJECT-TYPE
			SYNTAX	INTEGER
			MAX-ACCESS	read-only
			STATUS	current
			::= { hmWanMbusF1 41 }

hmWanMbusF1VIF12		OBJECT-TYPE
			SYNTAX	INTEGER
			MAX-ACCESS	read-only
			STATUS	current
			::= { hmWanMbusF1 42 }

hmWanMbusF1Value12		OBJECT-TYPE
			SYNTAX	INTEGER
			MAX-ACCESS	read-only
			STATUS	current
			::= { hmWanMbusF1 43 }

hmWanMbusF1VIF13		OBJECT-TYPE
			SYNTAX	INTEGER
			MAX-ACCESS	read-only
			STATUS	current
			::= { hmWanMbusF1 44 }

hmWanMbusF1Value13		OBJECT-TYPE
			SYNTAX	INTEGER
			MAX-ACCESS	read-only
			STATUS	current
			::= { hmWanMbusF1 45 }

hmWanMbusF1VIF14		OBJECT-TYPE
			SYNTAX	INTEGER
			MAX-ACCESS	read-only
			STATUS	current
			::= { hmWanMbusF1 46 }

hmWanMbusF1Value14		OBJECT-TYPE
			SYNTAX	INTEGER
			MAX-ACCESS	read-only
			STATUS	current
			::= { hmWanMbusF1 47 }

hmWanMbusF1VIF15		OBJECT-TYPE
			SYNTAX	INTEGER
			MAX-ACCESS	read-only
			STATUS	current
			::= { hmWanMbusF1 48 }

hmWanMbusF1Value15		OBJECT-TYPE
			SYNTAX	INTEGER
			MAX-ACCESS	read-only
			STATUS	current
			::= { hmWanMbusF1 49 }

hmWanMbusF1VIF16		OBJECT-TYPE
			SYNTAX	INTEGER
			MAX-ACCESS	read-only
			STATUS	current
			::= { hmWanMbusF1 50 }

hmWanMbusF1Value16		OBJECT-TYPE
			SYNTAX	INTEGER
			MAX-ACCESS	read-only
			STATUS	current
			::= { hmWanMbusF1 51 }

hmWanMbusF1VIF17		OBJECT-TYPE
			SYNTAX	INTEGER
			MAX-ACCESS	read-only
			STATUS	current
			::= { hmWanMbusF1 52 }

hmWanMbusF1Value17		OBJECT-TYPE
			SYNTAX	INTEGER
			MAX-ACCESS	read-only
			STATUS	current
			::= { hmWanMbusF1 53 }

hmWanMbusF1VIF18		OBJECT-TYPE
			SYNTAX	INTEGER
			MAX-ACCESS	read-only
			STATUS	current
			::= { hmWanMbusF1 54 }

hmWanMbusF1Value18		OBJECT-TYPE
			SYNTAX	INTEGER
			MAX-ACCESS	read-only
			STATUS	current
			::= { hmWanMbusF1 55 }

hmWanMbusF1VIF19		OBJECT-TYPE
			SYNTAX	INTEGER
			MAX-ACCESS	read-only
			STATUS	current
			::= { hmWanMbusF1 56 }

hmWanMbusF1Value19		OBJECT-TYPE
			SYNTAX	INTEGER
			MAX-ACCESS	read-only
			STATUS	current
			::= { hmWanMbusF1 57 }

hmWanMbusF1VIF1A		OBJECT-TYPE
			SYNTAX	INTEGER
			MAX-ACCESS	read-only
			STATUS	current
			::= { hmWanMbusF1 58 }

hmWanMbusF1Value1A		OBJECT-TYPE
			SYNTAX	INTEGER
			MAX-ACCESS	read-only
			STATUS	current
			::= { hmWanMbusF1 59 }

hmWanMbusF1VIF1B		OBJECT-TYPE
			SYNTAX	INTEGER
			MAX-ACCESS	read-only
			STATUS	current
			::= { hmWanMbusF1 60 }

hmWanMbusF1Value1B		OBJECT-TYPE
			SYNTAX	INTEGER
			MAX-ACCESS	read-only
			STATUS	current
			::= { hmWanMbusF1 61 }

hmWanMbusF1VIF1C		OBJECT-TYPE
			SYNTAX	INTEGER
			MAX-ACCESS	read-only
			STATUS	current
			::= { hmWanMbusF1 62 }

hmWanMbusF1Value1C		OBJECT-TYPE
			SYNTAX	INTEGER
			MAX-ACCESS	read-only
			STATUS	current
			::= { hmWanMbusF1 63 }

hmWanMbusF1VIF1D		OBJECT-TYPE
			SYNTAX	INTEGER
			MAX-ACCESS	read-only
			STATUS	current
			::= { hmWanMbusF1 64 }

hmWanMbusF1Value1D		OBJECT-TYPE
			SYNTAX	INTEGER
			MAX-ACCESS	read-only
			STATUS	current
			::= { hmWanMbusF1 65 }

hmWanMbusF1VIF1E		OBJECT-TYPE
			SYNTAX	INTEGER
			MAX-ACCESS	read-only
			STATUS	current
			::= { hmWanMbusF1 66 }

hmWanMbusF1Value1E		OBJECT-TYPE
			SYNTAX	INTEGER
			MAX-ACCESS	read-only
			STATUS	current
			::= { hmWanMbusF1 67 }

hmWanMbusF1VIF1F		OBJECT-TYPE
			SYNTAX	INTEGER
			MAX-ACCESS	read-only
			STATUS	current
			::= { hmWanMbusF1 68 }

hmWanMbusF1Value1F		OBJECT-TYPE
			SYNTAX	INTEGER
			MAX-ACCESS	read-only
			STATUS	current
			::= { hmWanMbusF1 69 }

hmWanMbusF1VIF20		OBJECT-TYPE
			SYNTAX	INTEGER
			MAX-ACCESS	read-only
			STATUS	current
			::= { hmWanMbusF1 70 }

hmWanMbusF1Value20		OBJECT-TYPE
			SYNTAX	INTEGER
			MAX-ACCESS	read-only
			STATUS	current
			::= { hmWanMbusF1 71 }

hmWanMbusF1VIF21		OBJECT-TYPE
			SYNTAX	INTEGER
			MAX-ACCESS	read-only
			STATUS	current
			::= { hmWanMbusF1 72 }

hmWanMbusF1Value21		OBJECT-TYPE
			SYNTAX	INTEGER
			MAX-ACCESS	read-only
			STATUS	current
			::= { hmWanMbusF1 73 }

hmWanMbusF1VIF22		OBJECT-TYPE
			SYNTAX	INTEGER
			MAX-ACCESS	read-only
			STATUS	current
			::= { hmWanMbusF1 74 }

hmWanMbusF1Value22		OBJECT-TYPE
			SYNTAX	INTEGER
			MAX-ACCESS	read-only
			STATUS	current
			::= { hmWanMbusF1 75 }

hmWanMbusF1VIF23		OBJECT-TYPE
			SYNTAX	INTEGER
			MAX-ACCESS	read-only
			STATUS	current
			::= { hmWanMbusF1 76 }

hmWanMbusF1Value23		OBJECT-TYPE
			SYNTAX	INTEGER
			MAX-ACCESS	read-only
			STATUS	current
			::= { hmWanMbusF1 77 }

hmWanMbusF1VIF24		OBJECT-TYPE
			SYNTAX	INTEGER
			MAX-ACCESS	read-only
			STATUS	current
			::= { hmWanMbusF1 78 }

hmWanMbusF1Value24		OBJECT-TYPE
			SYNTAX	INTEGER
			MAX-ACCESS	read-only
			STATUS	current
			::= { hmWanMbusF1 79 }

hmWanMbusF1VIF25		OBJECT-TYPE
			SYNTAX	INTEGER
			MAX-ACCESS	read-only
			STATUS	current
			::= { hmWanMbusF1 80 }

hmWanMbusF1Value25		OBJECT-TYPE
			SYNTAX	INTEGER
			MAX-ACCESS	read-only
			STATUS	current
			::= { hmWanMbusF1 81 }

hmWanMbusF1VIF26		OBJECT-TYPE
			SYNTAX	INTEGER
			MAX-ACCESS	read-only
			STATUS	current
			::= { hmWanMbusF1 82 }

hmWanMbusF1Value26		OBJECT-TYPE
			SYNTAX	INTEGER
			MAX-ACCESS	read-only
			STATUS	current
			::= { hmWanMbusF1 83 }

hmWanMbusF1VIF27		OBJECT-TYPE
			SYNTAX	INTEGER
			MAX-ACCESS	read-only
			STATUS	current
			::= { hmWanMbusF1 84 }

hmWanMbusF1Value27		OBJECT-TYPE
			SYNTAX	INTEGER
			MAX-ACCESS	read-only
			STATUS	current
			::= { hmWanMbusF1 85 }

hmWanMbusF1VIF28		OBJECT-TYPE
			SYNTAX	INTEGER
			MAX-ACCESS	read-only
			STATUS	current
			::= { hmWanMbusF1 86 }

hmWanMbusF1Value28		OBJECT-TYPE
			SYNTAX	INTEGER
			MAX-ACCESS	read-only
			STATUS	current
			::= { hmWanMbusF1 87 }

hmWanMbusF1VIF29		OBJECT-TYPE
			SYNTAX	INTEGER
			MAX-ACCESS	read-only
			STATUS	current
			::= { hmWanMbusF1 88 }

hmWanMbusF1Value29		OBJECT-TYPE
			SYNTAX	INTEGER
			MAX-ACCESS	read-only
			STATUS	current
			::= { hmWanMbusF1 89 }

hmWanMbusF1VIF2A		OBJECT-TYPE
			SYNTAX	INTEGER
			MAX-ACCESS	read-only
			STATUS	current
			::= { hmWanMbusF1 90 }

hmWanMbusF1Value2A		OBJECT-TYPE
			SYNTAX	INTEGER
			MAX-ACCESS	read-only
			STATUS	current
			::= { hmWanMbusF1 91 }

hmWanMbusF1VIF2B		OBJECT-TYPE
			SYNTAX	INTEGER
			MAX-ACCESS	read-only
			STATUS	current
			::= { hmWanMbusF1 92 }

hmWanMbusF1Value2B		OBJECT-TYPE
			SYNTAX	INTEGER
			MAX-ACCESS	read-only
			STATUS	current
			::= { hmWanMbusF1 93 }

hmWanMbusF1VIF2C		OBJECT-TYPE
			SYNTAX	INTEGER
			MAX-ACCESS	read-only
			STATUS	current
			::= { hmWanMbusF1 94 }

hmWanMbusF1Value2C		OBJECT-TYPE
			SYNTAX	INTEGER
			MAX-ACCESS	read-only
			STATUS	current
			::= { hmWanMbusF1 95 }

hmWanMbusF1VIF2D		OBJECT-TYPE
			SYNTAX	INTEGER
			MAX-ACCESS	read-only
			STATUS	current
			::= { hmWanMbusF1 96 }

hmWanMbusF1Value2D		OBJECT-TYPE
			SYNTAX	INTEGER
			MAX-ACCESS	read-only
			STATUS	current
			::= { hmWanMbusF1 97 }

hmWanMbusF1VIF2E		OBJECT-TYPE
			SYNTAX	INTEGER
			MAX-ACCESS	read-only
			STATUS	current
			::= { hmWanMbusF1 98 }

hmWanMbusF1Value2E		OBJECT-TYPE
			SYNTAX	INTEGER
			MAX-ACCESS	read-only
			STATUS	current
			::= { hmWanMbusF1 99 }

hmWanMbusF1VIF2F		OBJECT-TYPE
			SYNTAX	INTEGER
			MAX-ACCESS	read-only
			STATUS	current
			::= { hmWanMbusF1 100 }

hmWanMbusF1Value2F		OBJECT-TYPE
			SYNTAX	INTEGER
			MAX-ACCESS	read-only
			STATUS	current
			::= { hmWanMbusF1 101 }

hmWanMbusF2			OBJECT IDENTIFIER ::= { hmWanMbus 242 }

hmWanMbusF2IdNumber		OBJECT-TYPE
			SYNTAX	Gauge32
			MAX-ACCESS	read-only
			STATUS	current
			::= { hmWanMbusF2 1 }

hmWanMbusF2Manufacturer	OBJECT-TYPE
			SYNTAX	Gauge32
			MAX-ACCESS	read-only
			STATUS	current
			::= { hmWanMbusF2 2 }

hmWanMbusF2Version		OBJECT-TYPE
			SYNTAX	Gauge32
			MAX-ACCESS	read-only
			STATUS	current
			::= { hmWanMbusF2 3 }

hmWanMbusF2Medium		OBJECT-TYPE
			SYNTAX	Gauge32
			MAX-ACCESS	read-only
			STATUS	current
			::= { hmWanMbusF2 4 }

hmWanMbusF2Status		OBJECT-TYPE
			SYNTAX	Gauge32
			MAX-ACCESS	read-only
			STATUS	current
			::= { hmWanMbusF2 5 }

hmWanMbusF2VIF00		OBJECT-TYPE
			SYNTAX	INTEGER
			MAX-ACCESS	read-only
			STATUS	current
			::= { hmWanMbusF2 6 }

hmWanMbusF2Value00		OBJECT-TYPE
			SYNTAX	INTEGER
			MAX-ACCESS	read-only
			STATUS	current
			::= { hmWanMbusF2 7 }

hmWanMbusF2VIF01		OBJECT-TYPE
			SYNTAX	INTEGER
			MAX-ACCESS	read-only
			STATUS	current
			::= { hmWanMbusF2 8 }

hmWanMbusF2Value01		OBJECT-TYPE
			SYNTAX	INTEGER
			MAX-ACCESS	read-only
			STATUS	current
			::= { hmWanMbusF2 9 }

hmWanMbusF2VIF02		OBJECT-TYPE
			SYNTAX	INTEGER
			MAX-ACCESS	read-only
			STATUS	current
			::= { hmWanMbusF2 10 }

hmWanMbusF2Value02		OBJECT-TYPE
			SYNTAX	INTEGER
			MAX-ACCESS	read-only
			STATUS	current
			::= { hmWanMbusF2 11 }

hmWanMbusF2VIF03		OBJECT-TYPE
			SYNTAX	INTEGER
			MAX-ACCESS	read-only
			STATUS	current
			::= { hmWanMbusF2 12 }

hmWanMbusF2Value03		OBJECT-TYPE
			SYNTAX	INTEGER
			MAX-ACCESS	read-only
			STATUS	current
			::= { hmWanMbusF2 13 }

hmWanMbusF2VIF04		OBJECT-TYPE
			SYNTAX	INTEGER
			MAX-ACCESS	read-only
			STATUS	current
			::= { hmWanMbusF2 14 }

hmWanMbusF2Value04		OBJECT-TYPE
			SYNTAX	INTEGER
			MAX-ACCESS	read-only
			STATUS	current
			::= { hmWanMbusF2 15 }

hmWanMbusF2VIF05		OBJECT-TYPE
			SYNTAX	INTEGER
			MAX-ACCESS	read-only
			STATUS	current
			::= { hmWanMbusF2 16 }

hmWanMbusF2Value05		OBJECT-TYPE
			SYNTAX	INTEGER
			MAX-ACCESS	read-only
			STATUS	current
			::= { hmWanMbusF2 17 }

hmWanMbusF2VIF06		OBJECT-TYPE
			SYNTAX	INTEGER
			MAX-ACCESS	read-only
			STATUS	current
			::= { hmWanMbusF2 18 }

hmWanMbusF2Value06		OBJECT-TYPE
			SYNTAX	INTEGER
			MAX-ACCESS	read-only
			STATUS	current
			::= { hmWanMbusF2 19 }

hmWanMbusF2VIF07		OBJECT-TYPE
			SYNTAX	INTEGER
			MAX-ACCESS	read-only
			STATUS	current
			::= { hmWanMbusF2 20 }

hmWanMbusF2Value07		OBJECT-TYPE
			SYNTAX	INTEGER
			MAX-ACCESS	read-only
			STATUS	current
			::= { hmWanMbusF2 21 }

hmWanMbusF2VIF08		OBJECT-TYPE
			SYNTAX	INTEGER
			MAX-ACCESS	read-only
			STATUS	current
			::= { hmWanMbusF2 22 }

hmWanMbusF2Value08		OBJECT-TYPE
			SYNTAX	INTEGER
			MAX-ACCESS	read-only
			STATUS	current
			::= { hmWanMbusF2 23 }

hmWanMbusF2VIF09		OBJECT-TYPE
			SYNTAX	INTEGER
			MAX-ACCESS	read-only
			STATUS	current
			::= { hmWanMbusF2 24 }

hmWanMbusF2Value09		OBJECT-TYPE
			SYNTAX	INTEGER
			MAX-ACCESS	read-only
			STATUS	current
			::= { hmWanMbusF2 25 }

hmWanMbusF2VIF0A		OBJECT-TYPE
			SYNTAX	INTEGER
			MAX-ACCESS	read-only
			STATUS	current
			::= { hmWanMbusF2 26 }

hmWanMbusF2Value0A		OBJECT-TYPE
			SYNTAX	INTEGER
			MAX-ACCESS	read-only
			STATUS	current
			::= { hmWanMbusF2 27 }

hmWanMbusF2VIF0B		OBJECT-TYPE
			SYNTAX	INTEGER
			MAX-ACCESS	read-only
			STATUS	current
			::= { hmWanMbusF2 28 }

hmWanMbusF2Value0B		OBJECT-TYPE
			SYNTAX	INTEGER
			MAX-ACCESS	read-only
			STATUS	current
			::= { hmWanMbusF2 29 }

hmWanMbusF2VIF0C		OBJECT-TYPE
			SYNTAX	INTEGER
			MAX-ACCESS	read-only
			STATUS	current
			::= { hmWanMbusF2 30 }

hmWanMbusF2Value0C		OBJECT-TYPE
			SYNTAX	INTEGER
			MAX-ACCESS	read-only
			STATUS	current
			::= { hmWanMbusF2 31 }

hmWanMbusF2VIF0D		OBJECT-TYPE
			SYNTAX	INTEGER
			MAX-ACCESS	read-only
			STATUS	current
			::= { hmWanMbusF2 32 }

hmWanMbusF2Value0D		OBJECT-TYPE
			SYNTAX	INTEGER
			MAX-ACCESS	read-only
			STATUS	current
			::= { hmWanMbusF2 33 }

hmWanMbusF2VIF0E		OBJECT-TYPE
			SYNTAX	INTEGER
			MAX-ACCESS	read-only
			STATUS	current
			::= { hmWanMbusF2 34 }

hmWanMbusF2Value0E		OBJECT-TYPE
			SYNTAX	INTEGER
			MAX-ACCESS	read-only
			STATUS	current
			::= { hmWanMbusF2 35 }

hmWanMbusF2VIF0F		OBJECT-TYPE
			SYNTAX	INTEGER
			MAX-ACCESS	read-only
			STATUS	current
			::= { hmWanMbusF2 36 }

hmWanMbusF2Value0F		OBJECT-TYPE
			SYNTAX	INTEGER
			MAX-ACCESS	read-only
			STATUS	current
			::= { hmWanMbusF2 37 }

hmWanMbusF2VIF10		OBJECT-TYPE
			SYNTAX	INTEGER
			MAX-ACCESS	read-only
			STATUS	current
			::= { hmWanMbusF2 38 }

hmWanMbusF2Value10		OBJECT-TYPE
			SYNTAX	INTEGER
			MAX-ACCESS	read-only
			STATUS	current
			::= { hmWanMbusF2 39 }

hmWanMbusF2VIF11		OBJECT-TYPE
			SYNTAX	INTEGER
			MAX-ACCESS	read-only
			STATUS	current
			::= { hmWanMbusF2 40 }

hmWanMbusF2Value11		OBJECT-TYPE
			SYNTAX	INTEGER
			MAX-ACCESS	read-only
			STATUS	current
			::= { hmWanMbusF2 41 }

hmWanMbusF2VIF12		OBJECT-TYPE
			SYNTAX	INTEGER
			MAX-ACCESS	read-only
			STATUS	current
			::= { hmWanMbusF2 42 }

hmWanMbusF2Value12		OBJECT-TYPE
			SYNTAX	INTEGER
			MAX-ACCESS	read-only
			STATUS	current
			::= { hmWanMbusF2 43 }

hmWanMbusF2VIF13		OBJECT-TYPE
			SYNTAX	INTEGER
			MAX-ACCESS	read-only
			STATUS	current
			::= { hmWanMbusF2 44 }

hmWanMbusF2Value13		OBJECT-TYPE
			SYNTAX	INTEGER
			MAX-ACCESS	read-only
			STATUS	current
			::= { hmWanMbusF2 45 }

hmWanMbusF2VIF14		OBJECT-TYPE
			SYNTAX	INTEGER
			MAX-ACCESS	read-only
			STATUS	current
			::= { hmWanMbusF2 46 }

hmWanMbusF2Value14		OBJECT-TYPE
			SYNTAX	INTEGER
			MAX-ACCESS	read-only
			STATUS	current
			::= { hmWanMbusF2 47 }

hmWanMbusF2VIF15		OBJECT-TYPE
			SYNTAX	INTEGER
			MAX-ACCESS	read-only
			STATUS	current
			::= { hmWanMbusF2 48 }

hmWanMbusF2Value15		OBJECT-TYPE
			SYNTAX	INTEGER
			MAX-ACCESS	read-only
			STATUS	current
			::= { hmWanMbusF2 49 }

hmWanMbusF2VIF16		OBJECT-TYPE
			SYNTAX	INTEGER
			MAX-ACCESS	read-only
			STATUS	current
			::= { hmWanMbusF2 50 }

hmWanMbusF2Value16		OBJECT-TYPE
			SYNTAX	INTEGER
			MAX-ACCESS	read-only
			STATUS	current
			::= { hmWanMbusF2 51 }

hmWanMbusF2VIF17		OBJECT-TYPE
			SYNTAX	INTEGER
			MAX-ACCESS	read-only
			STATUS	current
			::= { hmWanMbusF2 52 }

hmWanMbusF2Value17		OBJECT-TYPE
			SYNTAX	INTEGER
			MAX-ACCESS	read-only
			STATUS	current
			::= { hmWanMbusF2 53 }

hmWanMbusF2VIF18		OBJECT-TYPE
			SYNTAX	INTEGER
			MAX-ACCESS	read-only
			STATUS	current
			::= { hmWanMbusF2 54 }

hmWanMbusF2Value18		OBJECT-TYPE
			SYNTAX	INTEGER
			MAX-ACCESS	read-only
			STATUS	current
			::= { hmWanMbusF2 55 }

hmWanMbusF2VIF19		OBJECT-TYPE
			SYNTAX	INTEGER
			MAX-ACCESS	read-only
			STATUS	current
			::= { hmWanMbusF2 56 }

hmWanMbusF2Value19		OBJECT-TYPE
			SYNTAX	INTEGER
			MAX-ACCESS	read-only
			STATUS	current
			::= { hmWanMbusF2 57 }

hmWanMbusF2VIF1A		OBJECT-TYPE
			SYNTAX	INTEGER
			MAX-ACCESS	read-only
			STATUS	current
			::= { hmWanMbusF2 58 }

hmWanMbusF2Value1A		OBJECT-TYPE
			SYNTAX	INTEGER
			MAX-ACCESS	read-only
			STATUS	current
			::= { hmWanMbusF2 59 }

hmWanMbusF2VIF1B		OBJECT-TYPE
			SYNTAX	INTEGER
			MAX-ACCESS	read-only
			STATUS	current
			::= { hmWanMbusF2 60 }

hmWanMbusF2Value1B		OBJECT-TYPE
			SYNTAX	INTEGER
			MAX-ACCESS	read-only
			STATUS	current
			::= { hmWanMbusF2 61 }

hmWanMbusF2VIF1C		OBJECT-TYPE
			SYNTAX	INTEGER
			MAX-ACCESS	read-only
			STATUS	current
			::= { hmWanMbusF2 62 }

hmWanMbusF2Value1C		OBJECT-TYPE
			SYNTAX	INTEGER
			MAX-ACCESS	read-only
			STATUS	current
			::= { hmWanMbusF2 63 }

hmWanMbusF2VIF1D		OBJECT-TYPE
			SYNTAX	INTEGER
			MAX-ACCESS	read-only
			STATUS	current
			::= { hmWanMbusF2 64 }

hmWanMbusF2Value1D		OBJECT-TYPE
			SYNTAX	INTEGER
			MAX-ACCESS	read-only
			STATUS	current
			::= { hmWanMbusF2 65 }

hmWanMbusF2VIF1E		OBJECT-TYPE
			SYNTAX	INTEGER
			MAX-ACCESS	read-only
			STATUS	current
			::= { hmWanMbusF2 66 }

hmWanMbusF2Value1E		OBJECT-TYPE
			SYNTAX	INTEGER
			MAX-ACCESS	read-only
			STATUS	current
			::= { hmWanMbusF2 67 }

hmWanMbusF2VIF1F		OBJECT-TYPE
			SYNTAX	INTEGER
			MAX-ACCESS	read-only
			STATUS	current
			::= { hmWanMbusF2 68 }

hmWanMbusF2Value1F		OBJECT-TYPE
			SYNTAX	INTEGER
			MAX-ACCESS	read-only
			STATUS	current
			::= { hmWanMbusF2 69 }

hmWanMbusF2VIF20		OBJECT-TYPE
			SYNTAX	INTEGER
			MAX-ACCESS	read-only
			STATUS	current
			::= { hmWanMbusF2 70 }

hmWanMbusF2Value20		OBJECT-TYPE
			SYNTAX	INTEGER
			MAX-ACCESS	read-only
			STATUS	current
			::= { hmWanMbusF2 71 }

hmWanMbusF2VIF21		OBJECT-TYPE
			SYNTAX	INTEGER
			MAX-ACCESS	read-only
			STATUS	current
			::= { hmWanMbusF2 72 }

hmWanMbusF2Value21		OBJECT-TYPE
			SYNTAX	INTEGER
			MAX-ACCESS	read-only
			STATUS	current
			::= { hmWanMbusF2 73 }

hmWanMbusF2VIF22		OBJECT-TYPE
			SYNTAX	INTEGER
			MAX-ACCESS	read-only
			STATUS	current
			::= { hmWanMbusF2 74 }

hmWanMbusF2Value22		OBJECT-TYPE
			SYNTAX	INTEGER
			MAX-ACCESS	read-only
			STATUS	current
			::= { hmWanMbusF2 75 }

hmWanMbusF2VIF23		OBJECT-TYPE
			SYNTAX	INTEGER
			MAX-ACCESS	read-only
			STATUS	current
			::= { hmWanMbusF2 76 }

hmWanMbusF2Value23		OBJECT-TYPE
			SYNTAX	INTEGER
			MAX-ACCESS	read-only
			STATUS	current
			::= { hmWanMbusF2 77 }

hmWanMbusF2VIF24		OBJECT-TYPE
			SYNTAX	INTEGER
			MAX-ACCESS	read-only
			STATUS	current
			::= { hmWanMbusF2 78 }

hmWanMbusF2Value24		OBJECT-TYPE
			SYNTAX	INTEGER
			MAX-ACCESS	read-only
			STATUS	current
			::= { hmWanMbusF2 79 }

hmWanMbusF2VIF25		OBJECT-TYPE
			SYNTAX	INTEGER
			MAX-ACCESS	read-only
			STATUS	current
			::= { hmWanMbusF2 80 }

hmWanMbusF2Value25		OBJECT-TYPE
			SYNTAX	INTEGER
			MAX-ACCESS	read-only
			STATUS	current
			::= { hmWanMbusF2 81 }

hmWanMbusF2VIF26		OBJECT-TYPE
			SYNTAX	INTEGER
			MAX-ACCESS	read-only
			STATUS	current
			::= { hmWanMbusF2 82 }

hmWanMbusF2Value26		OBJECT-TYPE
			SYNTAX	INTEGER
			MAX-ACCESS	read-only
			STATUS	current
			::= { hmWanMbusF2 83 }

hmWanMbusF2VIF27		OBJECT-TYPE
			SYNTAX	INTEGER
			MAX-ACCESS	read-only
			STATUS	current
			::= { hmWanMbusF2 84 }

hmWanMbusF2Value27		OBJECT-TYPE
			SYNTAX	INTEGER
			MAX-ACCESS	read-only
			STATUS	current
			::= { hmWanMbusF2 85 }

hmWanMbusF2VIF28		OBJECT-TYPE
			SYNTAX	INTEGER
			MAX-ACCESS	read-only
			STATUS	current
			::= { hmWanMbusF2 86 }

hmWanMbusF2Value28		OBJECT-TYPE
			SYNTAX	INTEGER
			MAX-ACCESS	read-only
			STATUS	current
			::= { hmWanMbusF2 87 }

hmWanMbusF2VIF29		OBJECT-TYPE
			SYNTAX	INTEGER
			MAX-ACCESS	read-only
			STATUS	current
			::= { hmWanMbusF2 88 }

hmWanMbusF2Value29		OBJECT-TYPE
			SYNTAX	INTEGER
			MAX-ACCESS	read-only
			STATUS	current
			::= { hmWanMbusF2 89 }

hmWanMbusF2VIF2A		OBJECT-TYPE
			SYNTAX	INTEGER
			MAX-ACCESS	read-only
			STATUS	current
			::= { hmWanMbusF2 90 }

hmWanMbusF2Value2A		OBJECT-TYPE
			SYNTAX	INTEGER
			MAX-ACCESS	read-only
			STATUS	current
			::= { hmWanMbusF2 91 }

hmWanMbusF2VIF2B		OBJECT-TYPE
			SYNTAX	INTEGER
			MAX-ACCESS	read-only
			STATUS	current
			::= { hmWanMbusF2 92 }

hmWanMbusF2Value2B		OBJECT-TYPE
			SYNTAX	INTEGER
			MAX-ACCESS	read-only
			STATUS	current
			::= { hmWanMbusF2 93 }

hmWanMbusF2VIF2C		OBJECT-TYPE
			SYNTAX	INTEGER
			MAX-ACCESS	read-only
			STATUS	current
			::= { hmWanMbusF2 94 }

hmWanMbusF2Value2C		OBJECT-TYPE
			SYNTAX	INTEGER
			MAX-ACCESS	read-only
			STATUS	current
			::= { hmWanMbusF2 95 }

hmWanMbusF2VIF2D		OBJECT-TYPE
			SYNTAX	INTEGER
			MAX-ACCESS	read-only
			STATUS	current
			::= { hmWanMbusF2 96 }

hmWanMbusF2Value2D		OBJECT-TYPE
			SYNTAX	INTEGER
			MAX-ACCESS	read-only
			STATUS	current
			::= { hmWanMbusF2 97 }

hmWanMbusF2VIF2E		OBJECT-TYPE
			SYNTAX	INTEGER
			MAX-ACCESS	read-only
			STATUS	current
			::= { hmWanMbusF2 98 }

hmWanMbusF2Value2E		OBJECT-TYPE
			SYNTAX	INTEGER
			MAX-ACCESS	read-only
			STATUS	current
			::= { hmWanMbusF2 99 }

hmWanMbusF2VIF2F		OBJECT-TYPE
			SYNTAX	INTEGER
			MAX-ACCESS	read-only
			STATUS	current
			::= { hmWanMbusF2 100 }

hmWanMbusF2Value2F		OBJECT-TYPE
			SYNTAX	INTEGER
			MAX-ACCESS	read-only
			STATUS	current
			::= { hmWanMbusF2 101 }

hmWanMbusF3			OBJECT IDENTIFIER ::= { hmWanMbus 243 }

hmWanMbusF3IdNumber		OBJECT-TYPE
			SYNTAX	Gauge32
			MAX-ACCESS	read-only
			STATUS	current
			::= { hmWanMbusF3 1 }

hmWanMbusF3Manufacturer	OBJECT-TYPE
			SYNTAX	Gauge32
			MAX-ACCESS	read-only
			STATUS	current
			::= { hmWanMbusF3 2 }

hmWanMbusF3Version		OBJECT-TYPE
			SYNTAX	Gauge32
			MAX-ACCESS	read-only
			STATUS	current
			::= { hmWanMbusF3 3 }

hmWanMbusF3Medium		OBJECT-TYPE
			SYNTAX	Gauge32
			MAX-ACCESS	read-only
			STATUS	current
			::= { hmWanMbusF3 4 }

hmWanMbusF3Status		OBJECT-TYPE
			SYNTAX	Gauge32
			MAX-ACCESS	read-only
			STATUS	current
			::= { hmWanMbusF3 5 }

hmWanMbusF3VIF00		OBJECT-TYPE
			SYNTAX	INTEGER
			MAX-ACCESS	read-only
			STATUS	current
			::= { hmWanMbusF3 6 }

hmWanMbusF3Value00		OBJECT-TYPE
			SYNTAX	INTEGER
			MAX-ACCESS	read-only
			STATUS	current
			::= { hmWanMbusF3 7 }

hmWanMbusF3VIF01		OBJECT-TYPE
			SYNTAX	INTEGER
			MAX-ACCESS	read-only
			STATUS	current
			::= { hmWanMbusF3 8 }

hmWanMbusF3Value01		OBJECT-TYPE
			SYNTAX	INTEGER
			MAX-ACCESS	read-only
			STATUS	current
			::= { hmWanMbusF3 9 }

hmWanMbusF3VIF02		OBJECT-TYPE
			SYNTAX	INTEGER
			MAX-ACCESS	read-only
			STATUS	current
			::= { hmWanMbusF3 10 }

hmWanMbusF3Value02		OBJECT-TYPE
			SYNTAX	INTEGER
			MAX-ACCESS	read-only
			STATUS	current
			::= { hmWanMbusF3 11 }

hmWanMbusF3VIF03		OBJECT-TYPE
			SYNTAX	INTEGER
			MAX-ACCESS	read-only
			STATUS	current
			::= { hmWanMbusF3 12 }

hmWanMbusF3Value03		OBJECT-TYPE
			SYNTAX	INTEGER
			MAX-ACCESS	read-only
			STATUS	current
			::= { hmWanMbusF3 13 }

hmWanMbusF3VIF04		OBJECT-TYPE
			SYNTAX	INTEGER
			MAX-ACCESS	read-only
			STATUS	current
			::= { hmWanMbusF3 14 }

hmWanMbusF3Value04		OBJECT-TYPE
			SYNTAX	INTEGER
			MAX-ACCESS	read-only
			STATUS	current
			::= { hmWanMbusF3 15 }

hmWanMbusF3VIF05		OBJECT-TYPE
			SYNTAX	INTEGER
			MAX-ACCESS	read-only
			STATUS	current
			::= { hmWanMbusF3 16 }

hmWanMbusF3Value05		OBJECT-TYPE
			SYNTAX	INTEGER
			MAX-ACCESS	read-only
			STATUS	current
			::= { hmWanMbusF3 17 }

hmWanMbusF3VIF06		OBJECT-TYPE
			SYNTAX	INTEGER
			MAX-ACCESS	read-only
			STATUS	current
			::= { hmWanMbusF3 18 }

hmWanMbusF3Value06		OBJECT-TYPE
			SYNTAX	INTEGER
			MAX-ACCESS	read-only
			STATUS	current
			::= { hmWanMbusF3 19 }

hmWanMbusF3VIF07		OBJECT-TYPE
			SYNTAX	INTEGER
			MAX-ACCESS	read-only
			STATUS	current
			::= { hmWanMbusF3 20 }

hmWanMbusF3Value07		OBJECT-TYPE
			SYNTAX	INTEGER
			MAX-ACCESS	read-only
			STATUS	current
			::= { hmWanMbusF3 21 }

hmWanMbusF3VIF08		OBJECT-TYPE
			SYNTAX	INTEGER
			MAX-ACCESS	read-only
			STATUS	current
			::= { hmWanMbusF3 22 }

hmWanMbusF3Value08		OBJECT-TYPE
			SYNTAX	INTEGER
			MAX-ACCESS	read-only
			STATUS	current
			::= { hmWanMbusF3 23 }

hmWanMbusF3VIF09		OBJECT-TYPE
			SYNTAX	INTEGER
			MAX-ACCESS	read-only
			STATUS	current
			::= { hmWanMbusF3 24 }

hmWanMbusF3Value09		OBJECT-TYPE
			SYNTAX	INTEGER
			MAX-ACCESS	read-only
			STATUS	current
			::= { hmWanMbusF3 25 }

hmWanMbusF3VIF0A		OBJECT-TYPE
			SYNTAX	INTEGER
			MAX-ACCESS	read-only
			STATUS	current
			::= { hmWanMbusF3 26 }

hmWanMbusF3Value0A		OBJECT-TYPE
			SYNTAX	INTEGER
			MAX-ACCESS	read-only
			STATUS	current
			::= { hmWanMbusF3 27 }

hmWanMbusF3VIF0B		OBJECT-TYPE
			SYNTAX	INTEGER
			MAX-ACCESS	read-only
			STATUS	current
			::= { hmWanMbusF3 28 }

hmWanMbusF3Value0B		OBJECT-TYPE
			SYNTAX	INTEGER
			MAX-ACCESS	read-only
			STATUS	current
			::= { hmWanMbusF3 29 }

hmWanMbusF3VIF0C		OBJECT-TYPE
			SYNTAX	INTEGER
			MAX-ACCESS	read-only
			STATUS	current
			::= { hmWanMbusF3 30 }

hmWanMbusF3Value0C		OBJECT-TYPE
			SYNTAX	INTEGER
			MAX-ACCESS	read-only
			STATUS	current
			::= { hmWanMbusF3 31 }

hmWanMbusF3VIF0D		OBJECT-TYPE
			SYNTAX	INTEGER
			MAX-ACCESS	read-only
			STATUS	current
			::= { hmWanMbusF3 32 }

hmWanMbusF3Value0D		OBJECT-TYPE
			SYNTAX	INTEGER
			MAX-ACCESS	read-only
			STATUS	current
			::= { hmWanMbusF3 33 }

hmWanMbusF3VIF0E		OBJECT-TYPE
			SYNTAX	INTEGER
			MAX-ACCESS	read-only
			STATUS	current
			::= { hmWanMbusF3 34 }

hmWanMbusF3Value0E		OBJECT-TYPE
			SYNTAX	INTEGER
			MAX-ACCESS	read-only
			STATUS	current
			::= { hmWanMbusF3 35 }

hmWanMbusF3VIF0F		OBJECT-TYPE
			SYNTAX	INTEGER
			MAX-ACCESS	read-only
			STATUS	current
			::= { hmWanMbusF3 36 }

hmWanMbusF3Value0F		OBJECT-TYPE
			SYNTAX	INTEGER
			MAX-ACCESS	read-only
			STATUS	current
			::= { hmWanMbusF3 37 }

hmWanMbusF3VIF10		OBJECT-TYPE
			SYNTAX	INTEGER
			MAX-ACCESS	read-only
			STATUS	current
			::= { hmWanMbusF3 38 }

hmWanMbusF3Value10		OBJECT-TYPE
			SYNTAX	INTEGER
			MAX-ACCESS	read-only
			STATUS	current
			::= { hmWanMbusF3 39 }

hmWanMbusF3VIF11		OBJECT-TYPE
			SYNTAX	INTEGER
			MAX-ACCESS	read-only
			STATUS	current
			::= { hmWanMbusF3 40 }

hmWanMbusF3Value11		OBJECT-TYPE
			SYNTAX	INTEGER
			MAX-ACCESS	read-only
			STATUS	current
			::= { hmWanMbusF3 41 }

hmWanMbusF3VIF12		OBJECT-TYPE
			SYNTAX	INTEGER
			MAX-ACCESS	read-only
			STATUS	current
			::= { hmWanMbusF3 42 }

hmWanMbusF3Value12		OBJECT-TYPE
			SYNTAX	INTEGER
			MAX-ACCESS	read-only
			STATUS	current
			::= { hmWanMbusF3 43 }

hmWanMbusF3VIF13		OBJECT-TYPE
			SYNTAX	INTEGER
			MAX-ACCESS	read-only
			STATUS	current
			::= { hmWanMbusF3 44 }

hmWanMbusF3Value13		OBJECT-TYPE
			SYNTAX	INTEGER
			MAX-ACCESS	read-only
			STATUS	current
			::= { hmWanMbusF3 45 }

hmWanMbusF3VIF14		OBJECT-TYPE
			SYNTAX	INTEGER
			MAX-ACCESS	read-only
			STATUS	current
			::= { hmWanMbusF3 46 }

hmWanMbusF3Value14		OBJECT-TYPE
			SYNTAX	INTEGER
			MAX-ACCESS	read-only
			STATUS	current
			::= { hmWanMbusF3 47 }

hmWanMbusF3VIF15		OBJECT-TYPE
			SYNTAX	INTEGER
			MAX-ACCESS	read-only
			STATUS	current
			::= { hmWanMbusF3 48 }

hmWanMbusF3Value15		OBJECT-TYPE
			SYNTAX	INTEGER
			MAX-ACCESS	read-only
			STATUS	current
			::= { hmWanMbusF3 49 }

hmWanMbusF3VIF16		OBJECT-TYPE
			SYNTAX	INTEGER
			MAX-ACCESS	read-only
			STATUS	current
			::= { hmWanMbusF3 50 }

hmWanMbusF3Value16		OBJECT-TYPE
			SYNTAX	INTEGER
			MAX-ACCESS	read-only
			STATUS	current
			::= { hmWanMbusF3 51 }

hmWanMbusF3VIF17		OBJECT-TYPE
			SYNTAX	INTEGER
			MAX-ACCESS	read-only
			STATUS	current
			::= { hmWanMbusF3 52 }

hmWanMbusF3Value17		OBJECT-TYPE
			SYNTAX	INTEGER
			MAX-ACCESS	read-only
			STATUS	current
			::= { hmWanMbusF3 53 }

hmWanMbusF3VIF18		OBJECT-TYPE
			SYNTAX	INTEGER
			MAX-ACCESS	read-only
			STATUS	current
			::= { hmWanMbusF3 54 }

hmWanMbusF3Value18		OBJECT-TYPE
			SYNTAX	INTEGER
			MAX-ACCESS	read-only
			STATUS	current
			::= { hmWanMbusF3 55 }

hmWanMbusF3VIF19		OBJECT-TYPE
			SYNTAX	INTEGER
			MAX-ACCESS	read-only
			STATUS	current
			::= { hmWanMbusF3 56 }

hmWanMbusF3Value19		OBJECT-TYPE
			SYNTAX	INTEGER
			MAX-ACCESS	read-only
			STATUS	current
			::= { hmWanMbusF3 57 }

hmWanMbusF3VIF1A		OBJECT-TYPE
			SYNTAX	INTEGER
			MAX-ACCESS	read-only
			STATUS	current
			::= { hmWanMbusF3 58 }

hmWanMbusF3Value1A		OBJECT-TYPE
			SYNTAX	INTEGER
			MAX-ACCESS	read-only
			STATUS	current
			::= { hmWanMbusF3 59 }

hmWanMbusF3VIF1B		OBJECT-TYPE
			SYNTAX	INTEGER
			MAX-ACCESS	read-only
			STATUS	current
			::= { hmWanMbusF3 60 }

hmWanMbusF3Value1B		OBJECT-TYPE
			SYNTAX	INTEGER
			MAX-ACCESS	read-only
			STATUS	current
			::= { hmWanMbusF3 61 }

hmWanMbusF3VIF1C		OBJECT-TYPE
			SYNTAX	INTEGER
			MAX-ACCESS	read-only
			STATUS	current
			::= { hmWanMbusF3 62 }

hmWanMbusF3Value1C		OBJECT-TYPE
			SYNTAX	INTEGER
			MAX-ACCESS	read-only
			STATUS	current
			::= { hmWanMbusF3 63 }

hmWanMbusF3VIF1D		OBJECT-TYPE
			SYNTAX	INTEGER
			MAX-ACCESS	read-only
			STATUS	current
			::= { hmWanMbusF3 64 }

hmWanMbusF3Value1D		OBJECT-TYPE
			SYNTAX	INTEGER
			MAX-ACCESS	read-only
			STATUS	current
			::= { hmWanMbusF3 65 }

hmWanMbusF3VIF1E		OBJECT-TYPE
			SYNTAX	INTEGER
			MAX-ACCESS	read-only
			STATUS	current
			::= { hmWanMbusF3 66 }

hmWanMbusF3Value1E		OBJECT-TYPE
			SYNTAX	INTEGER
			MAX-ACCESS	read-only
			STATUS	current
			::= { hmWanMbusF3 67 }

hmWanMbusF3VIF1F		OBJECT-TYPE
			SYNTAX	INTEGER
			MAX-ACCESS	read-only
			STATUS	current
			::= { hmWanMbusF3 68 }

hmWanMbusF3Value1F		OBJECT-TYPE
			SYNTAX	INTEGER
			MAX-ACCESS	read-only
			STATUS	current
			::= { hmWanMbusF3 69 }

hmWanMbusF3VIF20		OBJECT-TYPE
			SYNTAX	INTEGER
			MAX-ACCESS	read-only
			STATUS	current
			::= { hmWanMbusF3 70 }

hmWanMbusF3Value20		OBJECT-TYPE
			SYNTAX	INTEGER
			MAX-ACCESS	read-only
			STATUS	current
			::= { hmWanMbusF3 71 }

hmWanMbusF3VIF21		OBJECT-TYPE
			SYNTAX	INTEGER
			MAX-ACCESS	read-only
			STATUS	current
			::= { hmWanMbusF3 72 }

hmWanMbusF3Value21		OBJECT-TYPE
			SYNTAX	INTEGER
			MAX-ACCESS	read-only
			STATUS	current
			::= { hmWanMbusF3 73 }

hmWanMbusF3VIF22		OBJECT-TYPE
			SYNTAX	INTEGER
			MAX-ACCESS	read-only
			STATUS	current
			::= { hmWanMbusF3 74 }

hmWanMbusF3Value22		OBJECT-TYPE
			SYNTAX	INTEGER
			MAX-ACCESS	read-only
			STATUS	current
			::= { hmWanMbusF3 75 }

hmWanMbusF3VIF23		OBJECT-TYPE
			SYNTAX	INTEGER
			MAX-ACCESS	read-only
			STATUS	current
			::= { hmWanMbusF3 76 }

hmWanMbusF3Value23		OBJECT-TYPE
			SYNTAX	INTEGER
			MAX-ACCESS	read-only
			STATUS	current
			::= { hmWanMbusF3 77 }

hmWanMbusF3VIF24		OBJECT-TYPE
			SYNTAX	INTEGER
			MAX-ACCESS	read-only
			STATUS	current
			::= { hmWanMbusF3 78 }

hmWanMbusF3Value24		OBJECT-TYPE
			SYNTAX	INTEGER
			MAX-ACCESS	read-only
			STATUS	current
			::= { hmWanMbusF3 79 }

hmWanMbusF3VIF25		OBJECT-TYPE
			SYNTAX	INTEGER
			MAX-ACCESS	read-only
			STATUS	current
			::= { hmWanMbusF3 80 }

hmWanMbusF3Value25		OBJECT-TYPE
			SYNTAX	INTEGER
			MAX-ACCESS	read-only
			STATUS	current
			::= { hmWanMbusF3 81 }

hmWanMbusF3VIF26		OBJECT-TYPE
			SYNTAX	INTEGER
			MAX-ACCESS	read-only
			STATUS	current
			::= { hmWanMbusF3 82 }

hmWanMbusF3Value26		OBJECT-TYPE
			SYNTAX	INTEGER
			MAX-ACCESS	read-only
			STATUS	current
			::= { hmWanMbusF3 83 }

hmWanMbusF3VIF27		OBJECT-TYPE
			SYNTAX	INTEGER
			MAX-ACCESS	read-only
			STATUS	current
			::= { hmWanMbusF3 84 }

hmWanMbusF3Value27		OBJECT-TYPE
			SYNTAX	INTEGER
			MAX-ACCESS	read-only
			STATUS	current
			::= { hmWanMbusF3 85 }

hmWanMbusF3VIF28		OBJECT-TYPE
			SYNTAX	INTEGER
			MAX-ACCESS	read-only
			STATUS	current
			::= { hmWanMbusF3 86 }

hmWanMbusF3Value28		OBJECT-TYPE
			SYNTAX	INTEGER
			MAX-ACCESS	read-only
			STATUS	current
			::= { hmWanMbusF3 87 }

hmWanMbusF3VIF29		OBJECT-TYPE
			SYNTAX	INTEGER
			MAX-ACCESS	read-only
			STATUS	current
			::= { hmWanMbusF3 88 }

hmWanMbusF3Value29		OBJECT-TYPE
			SYNTAX	INTEGER
			MAX-ACCESS	read-only
			STATUS	current
			::= { hmWanMbusF3 89 }

hmWanMbusF3VIF2A		OBJECT-TYPE
			SYNTAX	INTEGER
			MAX-ACCESS	read-only
			STATUS	current
			::= { hmWanMbusF3 90 }

hmWanMbusF3Value2A		OBJECT-TYPE
			SYNTAX	INTEGER
			MAX-ACCESS	read-only
			STATUS	current
			::= { hmWanMbusF3 91 }

hmWanMbusF3VIF2B		OBJECT-TYPE
			SYNTAX	INTEGER
			MAX-ACCESS	read-only
			STATUS	current
			::= { hmWanMbusF3 92 }

hmWanMbusF3Value2B		OBJECT-TYPE
			SYNTAX	INTEGER
			MAX-ACCESS	read-only
			STATUS	current
			::= { hmWanMbusF3 93 }

hmWanMbusF3VIF2C		OBJECT-TYPE
			SYNTAX	INTEGER
			MAX-ACCESS	read-only
			STATUS	current
			::= { hmWanMbusF3 94 }

hmWanMbusF3Value2C		OBJECT-TYPE
			SYNTAX	INTEGER
			MAX-ACCESS	read-only
			STATUS	current
			::= { hmWanMbusF3 95 }

hmWanMbusF3VIF2D		OBJECT-TYPE
			SYNTAX	INTEGER
			MAX-ACCESS	read-only
			STATUS	current
			::= { hmWanMbusF3 96 }

hmWanMbusF3Value2D		OBJECT-TYPE
			SYNTAX	INTEGER
			MAX-ACCESS	read-only
			STATUS	current
			::= { hmWanMbusF3 97 }

hmWanMbusF3VIF2E		OBJECT-TYPE
			SYNTAX	INTEGER
			MAX-ACCESS	read-only
			STATUS	current
			::= { hmWanMbusF3 98 }

hmWanMbusF3Value2E		OBJECT-TYPE
			SYNTAX	INTEGER
			MAX-ACCESS	read-only
			STATUS	current
			::= { hmWanMbusF3 99 }

hmWanMbusF3VIF2F		OBJECT-TYPE
			SYNTAX	INTEGER
			MAX-ACCESS	read-only
			STATUS	current
			::= { hmWanMbusF3 100 }

hmWanMbusF3Value2F		OBJECT-TYPE
			SYNTAX	INTEGER
			MAX-ACCESS	read-only
			STATUS	current
			::= { hmWanMbusF3 101 }

hmWanMbusF4			OBJECT IDENTIFIER ::= { hmWanMbus 244 }

hmWanMbusF4IdNumber		OBJECT-TYPE
			SYNTAX	Gauge32
			MAX-ACCESS	read-only
			STATUS	current
			::= { hmWanMbusF4 1 }

hmWanMbusF4Manufacturer	OBJECT-TYPE
			SYNTAX	Gauge32
			MAX-ACCESS	read-only
			STATUS	current
			::= { hmWanMbusF4 2 }

hmWanMbusF4Version		OBJECT-TYPE
			SYNTAX	Gauge32
			MAX-ACCESS	read-only
			STATUS	current
			::= { hmWanMbusF4 3 }

hmWanMbusF4Medium		OBJECT-TYPE
			SYNTAX	Gauge32
			MAX-ACCESS	read-only
			STATUS	current
			::= { hmWanMbusF4 4 }

hmWanMbusF4Status		OBJECT-TYPE
			SYNTAX	Gauge32
			MAX-ACCESS	read-only
			STATUS	current
			::= { hmWanMbusF4 5 }

hmWanMbusF4VIF00		OBJECT-TYPE
			SYNTAX	INTEGER
			MAX-ACCESS	read-only
			STATUS	current
			::= { hmWanMbusF4 6 }

hmWanMbusF4Value00		OBJECT-TYPE
			SYNTAX	INTEGER
			MAX-ACCESS	read-only
			STATUS	current
			::= { hmWanMbusF4 7 }

hmWanMbusF4VIF01		OBJECT-TYPE
			SYNTAX	INTEGER
			MAX-ACCESS	read-only
			STATUS	current
			::= { hmWanMbusF4 8 }

hmWanMbusF4Value01		OBJECT-TYPE
			SYNTAX	INTEGER
			MAX-ACCESS	read-only
			STATUS	current
			::= { hmWanMbusF4 9 }

hmWanMbusF4VIF02		OBJECT-TYPE
			SYNTAX	INTEGER
			MAX-ACCESS	read-only
			STATUS	current
			::= { hmWanMbusF4 10 }

hmWanMbusF4Value02		OBJECT-TYPE
			SYNTAX	INTEGER
			MAX-ACCESS	read-only
			STATUS	current
			::= { hmWanMbusF4 11 }

hmWanMbusF4VIF03		OBJECT-TYPE
			SYNTAX	INTEGER
			MAX-ACCESS	read-only
			STATUS	current
			::= { hmWanMbusF4 12 }

hmWanMbusF4Value03		OBJECT-TYPE
			SYNTAX	INTEGER
			MAX-ACCESS	read-only
			STATUS	current
			::= { hmWanMbusF4 13 }

hmWanMbusF4VIF04		OBJECT-TYPE
			SYNTAX	INTEGER
			MAX-ACCESS	read-only
			STATUS	current
			::= { hmWanMbusF4 14 }

hmWanMbusF4Value04		OBJECT-TYPE
			SYNTAX	INTEGER
			MAX-ACCESS	read-only
			STATUS	current
			::= { hmWanMbusF4 15 }

hmWanMbusF4VIF05		OBJECT-TYPE
			SYNTAX	INTEGER
			MAX-ACCESS	read-only
			STATUS	current
			::= { hmWanMbusF4 16 }

hmWanMbusF4Value05		OBJECT-TYPE
			SYNTAX	INTEGER
			MAX-ACCESS	read-only
			STATUS	current
			::= { hmWanMbusF4 17 }

hmWanMbusF4VIF06		OBJECT-TYPE
			SYNTAX	INTEGER
			MAX-ACCESS	read-only
			STATUS	current
			::= { hmWanMbusF4 18 }

hmWanMbusF4Value06		OBJECT-TYPE
			SYNTAX	INTEGER
			MAX-ACCESS	read-only
			STATUS	current
			::= { hmWanMbusF4 19 }

hmWanMbusF4VIF07		OBJECT-TYPE
			SYNTAX	INTEGER
			MAX-ACCESS	read-only
			STATUS	current
			::= { hmWanMbusF4 20 }

hmWanMbusF4Value07		OBJECT-TYPE
			SYNTAX	INTEGER
			MAX-ACCESS	read-only
			STATUS	current
			::= { hmWanMbusF4 21 }

hmWanMbusF4VIF08		OBJECT-TYPE
			SYNTAX	INTEGER
			MAX-ACCESS	read-only
			STATUS	current
			::= { hmWanMbusF4 22 }

hmWanMbusF4Value08		OBJECT-TYPE
			SYNTAX	INTEGER
			MAX-ACCESS	read-only
			STATUS	current
			::= { hmWanMbusF4 23 }

hmWanMbusF4VIF09		OBJECT-TYPE
			SYNTAX	INTEGER
			MAX-ACCESS	read-only
			STATUS	current
			::= { hmWanMbusF4 24 }

hmWanMbusF4Value09		OBJECT-TYPE
			SYNTAX	INTEGER
			MAX-ACCESS	read-only
			STATUS	current
			::= { hmWanMbusF4 25 }

hmWanMbusF4VIF0A		OBJECT-TYPE
			SYNTAX	INTEGER
			MAX-ACCESS	read-only
			STATUS	current
			::= { hmWanMbusF4 26 }

hmWanMbusF4Value0A		OBJECT-TYPE
			SYNTAX	INTEGER
			MAX-ACCESS	read-only
			STATUS	current
			::= { hmWanMbusF4 27 }

hmWanMbusF4VIF0B		OBJECT-TYPE
			SYNTAX	INTEGER
			MAX-ACCESS	read-only
			STATUS	current
			::= { hmWanMbusF4 28 }

hmWanMbusF4Value0B		OBJECT-TYPE
			SYNTAX	INTEGER
			MAX-ACCESS	read-only
			STATUS	current
			::= { hmWanMbusF4 29 }

hmWanMbusF4VIF0C		OBJECT-TYPE
			SYNTAX	INTEGER
			MAX-ACCESS	read-only
			STATUS	current
			::= { hmWanMbusF4 30 }

hmWanMbusF4Value0C		OBJECT-TYPE
			SYNTAX	INTEGER
			MAX-ACCESS	read-only
			STATUS	current
			::= { hmWanMbusF4 31 }

hmWanMbusF4VIF0D		OBJECT-TYPE
			SYNTAX	INTEGER
			MAX-ACCESS	read-only
			STATUS	current
			::= { hmWanMbusF4 32 }

hmWanMbusF4Value0D		OBJECT-TYPE
			SYNTAX	INTEGER
			MAX-ACCESS	read-only
			STATUS	current
			::= { hmWanMbusF4 33 }

hmWanMbusF4VIF0E		OBJECT-TYPE
			SYNTAX	INTEGER
			MAX-ACCESS	read-only
			STATUS	current
			::= { hmWanMbusF4 34 }

hmWanMbusF4Value0E		OBJECT-TYPE
			SYNTAX	INTEGER
			MAX-ACCESS	read-only
			STATUS	current
			::= { hmWanMbusF4 35 }

hmWanMbusF4VIF0F		OBJECT-TYPE
			SYNTAX	INTEGER
			MAX-ACCESS	read-only
			STATUS	current
			::= { hmWanMbusF4 36 }

hmWanMbusF4Value0F		OBJECT-TYPE
			SYNTAX	INTEGER
			MAX-ACCESS	read-only
			STATUS	current
			::= { hmWanMbusF4 37 }

hmWanMbusF4VIF10		OBJECT-TYPE
			SYNTAX	INTEGER
			MAX-ACCESS	read-only
			STATUS	current
			::= { hmWanMbusF4 38 }

hmWanMbusF4Value10		OBJECT-TYPE
			SYNTAX	INTEGER
			MAX-ACCESS	read-only
			STATUS	current
			::= { hmWanMbusF4 39 }

hmWanMbusF4VIF11		OBJECT-TYPE
			SYNTAX	INTEGER
			MAX-ACCESS	read-only
			STATUS	current
			::= { hmWanMbusF4 40 }

hmWanMbusF4Value11		OBJECT-TYPE
			SYNTAX	INTEGER
			MAX-ACCESS	read-only
			STATUS	current
			::= { hmWanMbusF4 41 }

hmWanMbusF4VIF12		OBJECT-TYPE
			SYNTAX	INTEGER
			MAX-ACCESS	read-only
			STATUS	current
			::= { hmWanMbusF4 42 }

hmWanMbusF4Value12		OBJECT-TYPE
			SYNTAX	INTEGER
			MAX-ACCESS	read-only
			STATUS	current
			::= { hmWanMbusF4 43 }

hmWanMbusF4VIF13		OBJECT-TYPE
			SYNTAX	INTEGER
			MAX-ACCESS	read-only
			STATUS	current
			::= { hmWanMbusF4 44 }

hmWanMbusF4Value13		OBJECT-TYPE
			SYNTAX	INTEGER
			MAX-ACCESS	read-only
			STATUS	current
			::= { hmWanMbusF4 45 }

hmWanMbusF4VIF14		OBJECT-TYPE
			SYNTAX	INTEGER
			MAX-ACCESS	read-only
			STATUS	current
			::= { hmWanMbusF4 46 }

hmWanMbusF4Value14		OBJECT-TYPE
			SYNTAX	INTEGER
			MAX-ACCESS	read-only
			STATUS	current
			::= { hmWanMbusF4 47 }

hmWanMbusF4VIF15		OBJECT-TYPE
			SYNTAX	INTEGER
			MAX-ACCESS	read-only
			STATUS	current
			::= { hmWanMbusF4 48 }

hmWanMbusF4Value15		OBJECT-TYPE
			SYNTAX	INTEGER
			MAX-ACCESS	read-only
			STATUS	current
			::= { hmWanMbusF4 49 }

hmWanMbusF4VIF16		OBJECT-TYPE
			SYNTAX	INTEGER
			MAX-ACCESS	read-only
			STATUS	current
			::= { hmWanMbusF4 50 }

hmWanMbusF4Value16		OBJECT-TYPE
			SYNTAX	INTEGER
			MAX-ACCESS	read-only
			STATUS	current
			::= { hmWanMbusF4 51 }

hmWanMbusF4VIF17		OBJECT-TYPE
			SYNTAX	INTEGER
			MAX-ACCESS	read-only
			STATUS	current
			::= { hmWanMbusF4 52 }

hmWanMbusF4Value17		OBJECT-TYPE
			SYNTAX	INTEGER
			MAX-ACCESS	read-only
			STATUS	current
			::= { hmWanMbusF4 53 }

hmWanMbusF4VIF18		OBJECT-TYPE
			SYNTAX	INTEGER
			MAX-ACCESS	read-only
			STATUS	current
			::= { hmWanMbusF4 54 }

hmWanMbusF4Value18		OBJECT-TYPE
			SYNTAX	INTEGER
			MAX-ACCESS	read-only
			STATUS	current
			::= { hmWanMbusF4 55 }

hmWanMbusF4VIF19		OBJECT-TYPE
			SYNTAX	INTEGER
			MAX-ACCESS	read-only
			STATUS	current
			::= { hmWanMbusF4 56 }

hmWanMbusF4Value19		OBJECT-TYPE
			SYNTAX	INTEGER
			MAX-ACCESS	read-only
			STATUS	current
			::= { hmWanMbusF4 57 }

hmWanMbusF4VIF1A		OBJECT-TYPE
			SYNTAX	INTEGER
			MAX-ACCESS	read-only
			STATUS	current
			::= { hmWanMbusF4 58 }

hmWanMbusF4Value1A		OBJECT-TYPE
			SYNTAX	INTEGER
			MAX-ACCESS	read-only
			STATUS	current
			::= { hmWanMbusF4 59 }

hmWanMbusF4VIF1B		OBJECT-TYPE
			SYNTAX	INTEGER
			MAX-ACCESS	read-only
			STATUS	current
			::= { hmWanMbusF4 60 }

hmWanMbusF4Value1B		OBJECT-TYPE
			SYNTAX	INTEGER
			MAX-ACCESS	read-only
			STATUS	current
			::= { hmWanMbusF4 61 }

hmWanMbusF4VIF1C		OBJECT-TYPE
			SYNTAX	INTEGER
			MAX-ACCESS	read-only
			STATUS	current
			::= { hmWanMbusF4 62 }

hmWanMbusF4Value1C		OBJECT-TYPE
			SYNTAX	INTEGER
			MAX-ACCESS	read-only
			STATUS	current
			::= { hmWanMbusF4 63 }

hmWanMbusF4VIF1D		OBJECT-TYPE
			SYNTAX	INTEGER
			MAX-ACCESS	read-only
			STATUS	current
			::= { hmWanMbusF4 64 }

hmWanMbusF4Value1D		OBJECT-TYPE
			SYNTAX	INTEGER
			MAX-ACCESS	read-only
			STATUS	current
			::= { hmWanMbusF4 65 }

hmWanMbusF4VIF1E		OBJECT-TYPE
			SYNTAX	INTEGER
			MAX-ACCESS	read-only
			STATUS	current
			::= { hmWanMbusF4 66 }

hmWanMbusF4Value1E		OBJECT-TYPE
			SYNTAX	INTEGER
			MAX-ACCESS	read-only
			STATUS	current
			::= { hmWanMbusF4 67 }

hmWanMbusF4VIF1F		OBJECT-TYPE
			SYNTAX	INTEGER
			MAX-ACCESS	read-only
			STATUS	current
			::= { hmWanMbusF4 68 }

hmWanMbusF4Value1F		OBJECT-TYPE
			SYNTAX	INTEGER
			MAX-ACCESS	read-only
			STATUS	current
			::= { hmWanMbusF4 69 }

hmWanMbusF4VIF20		OBJECT-TYPE
			SYNTAX	INTEGER
			MAX-ACCESS	read-only
			STATUS	current
			::= { hmWanMbusF4 70 }

hmWanMbusF4Value20		OBJECT-TYPE
			SYNTAX	INTEGER
			MAX-ACCESS	read-only
			STATUS	current
			::= { hmWanMbusF4 71 }

hmWanMbusF4VIF21		OBJECT-TYPE
			SYNTAX	INTEGER
			MAX-ACCESS	read-only
			STATUS	current
			::= { hmWanMbusF4 72 }

hmWanMbusF4Value21		OBJECT-TYPE
			SYNTAX	INTEGER
			MAX-ACCESS	read-only
			STATUS	current
			::= { hmWanMbusF4 73 }

hmWanMbusF4VIF22		OBJECT-TYPE
			SYNTAX	INTEGER
			MAX-ACCESS	read-only
			STATUS	current
			::= { hmWanMbusF4 74 }

hmWanMbusF4Value22		OBJECT-TYPE
			SYNTAX	INTEGER
			MAX-ACCESS	read-only
			STATUS	current
			::= { hmWanMbusF4 75 }

hmWanMbusF4VIF23		OBJECT-TYPE
			SYNTAX	INTEGER
			MAX-ACCESS	read-only
			STATUS	current
			::= { hmWanMbusF4 76 }

hmWanMbusF4Value23		OBJECT-TYPE
			SYNTAX	INTEGER
			MAX-ACCESS	read-only
			STATUS	current
			::= { hmWanMbusF4 77 }

hmWanMbusF4VIF24		OBJECT-TYPE
			SYNTAX	INTEGER
			MAX-ACCESS	read-only
			STATUS	current
			::= { hmWanMbusF4 78 }

hmWanMbusF4Value24		OBJECT-TYPE
			SYNTAX	INTEGER
			MAX-ACCESS	read-only
			STATUS	current
			::= { hmWanMbusF4 79 }

hmWanMbusF4VIF25		OBJECT-TYPE
			SYNTAX	INTEGER
			MAX-ACCESS	read-only
			STATUS	current
			::= { hmWanMbusF4 80 }

hmWanMbusF4Value25		OBJECT-TYPE
			SYNTAX	INTEGER
			MAX-ACCESS	read-only
			STATUS	current
			::= { hmWanMbusF4 81 }

hmWanMbusF4VIF26		OBJECT-TYPE
			SYNTAX	INTEGER
			MAX-ACCESS	read-only
			STATUS	current
			::= { hmWanMbusF4 82 }

hmWanMbusF4Value26		OBJECT-TYPE
			SYNTAX	INTEGER
			MAX-ACCESS	read-only
			STATUS	current
			::= { hmWanMbusF4 83 }

hmWanMbusF4VIF27		OBJECT-TYPE
			SYNTAX	INTEGER
			MAX-ACCESS	read-only
			STATUS	current
			::= { hmWanMbusF4 84 }

hmWanMbusF4Value27		OBJECT-TYPE
			SYNTAX	INTEGER
			MAX-ACCESS	read-only
			STATUS	current
			::= { hmWanMbusF4 85 }

hmWanMbusF4VIF28		OBJECT-TYPE
			SYNTAX	INTEGER
			MAX-ACCESS	read-only
			STATUS	current
			::= { hmWanMbusF4 86 }

hmWanMbusF4Value28		OBJECT-TYPE
			SYNTAX	INTEGER
			MAX-ACCESS	read-only
			STATUS	current
			::= { hmWanMbusF4 87 }

hmWanMbusF4VIF29		OBJECT-TYPE
			SYNTAX	INTEGER
			MAX-ACCESS	read-only
			STATUS	current
			::= { hmWanMbusF4 88 }

hmWanMbusF4Value29		OBJECT-TYPE
			SYNTAX	INTEGER
			MAX-ACCESS	read-only
			STATUS	current
			::= { hmWanMbusF4 89 }

hmWanMbusF4VIF2A		OBJECT-TYPE
			SYNTAX	INTEGER
			MAX-ACCESS	read-only
			STATUS	current
			::= { hmWanMbusF4 90 }

hmWanMbusF4Value2A		OBJECT-TYPE
			SYNTAX	INTEGER
			MAX-ACCESS	read-only
			STATUS	current
			::= { hmWanMbusF4 91 }

hmWanMbusF4VIF2B		OBJECT-TYPE
			SYNTAX	INTEGER
			MAX-ACCESS	read-only
			STATUS	current
			::= { hmWanMbusF4 92 }

hmWanMbusF4Value2B		OBJECT-TYPE
			SYNTAX	INTEGER
			MAX-ACCESS	read-only
			STATUS	current
			::= { hmWanMbusF4 93 }

hmWanMbusF4VIF2C		OBJECT-TYPE
			SYNTAX	INTEGER
			MAX-ACCESS	read-only
			STATUS	current
			::= { hmWanMbusF4 94 }

hmWanMbusF4Value2C		OBJECT-TYPE
			SYNTAX	INTEGER
			MAX-ACCESS	read-only
			STATUS	current
			::= { hmWanMbusF4 95 }

hmWanMbusF4VIF2D		OBJECT-TYPE
			SYNTAX	INTEGER
			MAX-ACCESS	read-only
			STATUS	current
			::= { hmWanMbusF4 96 }

hmWanMbusF4Value2D		OBJECT-TYPE
			SYNTAX	INTEGER
			MAX-ACCESS	read-only
			STATUS	current
			::= { hmWanMbusF4 97 }

hmWanMbusF4VIF2E		OBJECT-TYPE
			SYNTAX	INTEGER
			MAX-ACCESS	read-only
			STATUS	current
			::= { hmWanMbusF4 98 }

hmWanMbusF4Value2E		OBJECT-TYPE
			SYNTAX	INTEGER
			MAX-ACCESS	read-only
			STATUS	current
			::= { hmWanMbusF4 99 }

hmWanMbusF4VIF2F		OBJECT-TYPE
			SYNTAX	INTEGER
			MAX-ACCESS	read-only
			STATUS	current
			::= { hmWanMbusF4 100 }

hmWanMbusF4Value2F		OBJECT-TYPE
			SYNTAX	INTEGER
			MAX-ACCESS	read-only
			STATUS	current
			::= { hmWanMbusF4 101 }

hmWanMbusF5			OBJECT IDENTIFIER ::= { hmWanMbus 245 }

hmWanMbusF5IdNumber		OBJECT-TYPE
			SYNTAX	Gauge32
			MAX-ACCESS	read-only
			STATUS	current
			::= { hmWanMbusF5 1 }

hmWanMbusF5Manufacturer	OBJECT-TYPE
			SYNTAX	Gauge32
			MAX-ACCESS	read-only
			STATUS	current
			::= { hmWanMbusF5 2 }

hmWanMbusF5Version		OBJECT-TYPE
			SYNTAX	Gauge32
			MAX-ACCESS	read-only
			STATUS	current
			::= { hmWanMbusF5 3 }

hmWanMbusF5Medium		OBJECT-TYPE
			SYNTAX	Gauge32
			MAX-ACCESS	read-only
			STATUS	current
			::= { hmWanMbusF5 4 }

hmWanMbusF5Status		OBJECT-TYPE
			SYNTAX	Gauge32
			MAX-ACCESS	read-only
			STATUS	current
			::= { hmWanMbusF5 5 }

hmWanMbusF5VIF00		OBJECT-TYPE
			SYNTAX	INTEGER
			MAX-ACCESS	read-only
			STATUS	current
			::= { hmWanMbusF5 6 }

hmWanMbusF5Value00		OBJECT-TYPE
			SYNTAX	INTEGER
			MAX-ACCESS	read-only
			STATUS	current
			::= { hmWanMbusF5 7 }

hmWanMbusF5VIF01		OBJECT-TYPE
			SYNTAX	INTEGER
			MAX-ACCESS	read-only
			STATUS	current
			::= { hmWanMbusF5 8 }

hmWanMbusF5Value01		OBJECT-TYPE
			SYNTAX	INTEGER
			MAX-ACCESS	read-only
			STATUS	current
			::= { hmWanMbusF5 9 }

hmWanMbusF5VIF02		OBJECT-TYPE
			SYNTAX	INTEGER
			MAX-ACCESS	read-only
			STATUS	current
			::= { hmWanMbusF5 10 }

hmWanMbusF5Value02		OBJECT-TYPE
			SYNTAX	INTEGER
			MAX-ACCESS	read-only
			STATUS	current
			::= { hmWanMbusF5 11 }

hmWanMbusF5VIF03		OBJECT-TYPE
			SYNTAX	INTEGER
			MAX-ACCESS	read-only
			STATUS	current
			::= { hmWanMbusF5 12 }

hmWanMbusF5Value03		OBJECT-TYPE
			SYNTAX	INTEGER
			MAX-ACCESS	read-only
			STATUS	current
			::= { hmWanMbusF5 13 }

hmWanMbusF5VIF04		OBJECT-TYPE
			SYNTAX	INTEGER
			MAX-ACCESS	read-only
			STATUS	current
			::= { hmWanMbusF5 14 }

hmWanMbusF5Value04		OBJECT-TYPE
			SYNTAX	INTEGER
			MAX-ACCESS	read-only
			STATUS	current
			::= { hmWanMbusF5 15 }

hmWanMbusF5VIF05		OBJECT-TYPE
			SYNTAX	INTEGER
			MAX-ACCESS	read-only
			STATUS	current
			::= { hmWanMbusF5 16 }

hmWanMbusF5Value05		OBJECT-TYPE
			SYNTAX	INTEGER
			MAX-ACCESS	read-only
			STATUS	current
			::= { hmWanMbusF5 17 }

hmWanMbusF5VIF06		OBJECT-TYPE
			SYNTAX	INTEGER
			MAX-ACCESS	read-only
			STATUS	current
			::= { hmWanMbusF5 18 }

hmWanMbusF5Value06		OBJECT-TYPE
			SYNTAX	INTEGER
			MAX-ACCESS	read-only
			STATUS	current
			::= { hmWanMbusF5 19 }

hmWanMbusF5VIF07		OBJECT-TYPE
			SYNTAX	INTEGER
			MAX-ACCESS	read-only
			STATUS	current
			::= { hmWanMbusF5 20 }

hmWanMbusF5Value07		OBJECT-TYPE
			SYNTAX	INTEGER
			MAX-ACCESS	read-only
			STATUS	current
			::= { hmWanMbusF5 21 }

hmWanMbusF5VIF08		OBJECT-TYPE
			SYNTAX	INTEGER
			MAX-ACCESS	read-only
			STATUS	current
			::= { hmWanMbusF5 22 }

hmWanMbusF5Value08		OBJECT-TYPE
			SYNTAX	INTEGER
			MAX-ACCESS	read-only
			STATUS	current
			::= { hmWanMbusF5 23 }

hmWanMbusF5VIF09		OBJECT-TYPE
			SYNTAX	INTEGER
			MAX-ACCESS	read-only
			STATUS	current
			::= { hmWanMbusF5 24 }

hmWanMbusF5Value09		OBJECT-TYPE
			SYNTAX	INTEGER
			MAX-ACCESS	read-only
			STATUS	current
			::= { hmWanMbusF5 25 }

hmWanMbusF5VIF0A		OBJECT-TYPE
			SYNTAX	INTEGER
			MAX-ACCESS	read-only
			STATUS	current
			::= { hmWanMbusF5 26 }

hmWanMbusF5Value0A		OBJECT-TYPE
			SYNTAX	INTEGER
			MAX-ACCESS	read-only
			STATUS	current
			::= { hmWanMbusF5 27 }

hmWanMbusF5VIF0B		OBJECT-TYPE
			SYNTAX	INTEGER
			MAX-ACCESS	read-only
			STATUS	current
			::= { hmWanMbusF5 28 }

hmWanMbusF5Value0B		OBJECT-TYPE
			SYNTAX	INTEGER
			MAX-ACCESS	read-only
			STATUS	current
			::= { hmWanMbusF5 29 }

hmWanMbusF5VIF0C		OBJECT-TYPE
			SYNTAX	INTEGER
			MAX-ACCESS	read-only
			STATUS	current
			::= { hmWanMbusF5 30 }

hmWanMbusF5Value0C		OBJECT-TYPE
			SYNTAX	INTEGER
			MAX-ACCESS	read-only
			STATUS	current
			::= { hmWanMbusF5 31 }

hmWanMbusF5VIF0D		OBJECT-TYPE
			SYNTAX	INTEGER
			MAX-ACCESS	read-only
			STATUS	current
			::= { hmWanMbusF5 32 }

hmWanMbusF5Value0D		OBJECT-TYPE
			SYNTAX	INTEGER
			MAX-ACCESS	read-only
			STATUS	current
			::= { hmWanMbusF5 33 }

hmWanMbusF5VIF0E		OBJECT-TYPE
			SYNTAX	INTEGER
			MAX-ACCESS	read-only
			STATUS	current
			::= { hmWanMbusF5 34 }

hmWanMbusF5Value0E		OBJECT-TYPE
			SYNTAX	INTEGER
			MAX-ACCESS	read-only
			STATUS	current
			::= { hmWanMbusF5 35 }

hmWanMbusF5VIF0F		OBJECT-TYPE
			SYNTAX	INTEGER
			MAX-ACCESS	read-only
			STATUS	current
			::= { hmWanMbusF5 36 }

hmWanMbusF5Value0F		OBJECT-TYPE
			SYNTAX	INTEGER
			MAX-ACCESS	read-only
			STATUS	current
			::= { hmWanMbusF5 37 }

hmWanMbusF5VIF10		OBJECT-TYPE
			SYNTAX	INTEGER
			MAX-ACCESS	read-only
			STATUS	current
			::= { hmWanMbusF5 38 }

hmWanMbusF5Value10		OBJECT-TYPE
			SYNTAX	INTEGER
			MAX-ACCESS	read-only
			STATUS	current
			::= { hmWanMbusF5 39 }

hmWanMbusF5VIF11		OBJECT-TYPE
			SYNTAX	INTEGER
			MAX-ACCESS	read-only
			STATUS	current
			::= { hmWanMbusF5 40 }

hmWanMbusF5Value11		OBJECT-TYPE
			SYNTAX	INTEGER
			MAX-ACCESS	read-only
			STATUS	current
			::= { hmWanMbusF5 41 }

hmWanMbusF5VIF12		OBJECT-TYPE
			SYNTAX	INTEGER
			MAX-ACCESS	read-only
			STATUS	current
			::= { hmWanMbusF5 42 }

hmWanMbusF5Value12		OBJECT-TYPE
			SYNTAX	INTEGER
			MAX-ACCESS	read-only
			STATUS	current
			::= { hmWanMbusF5 43 }

hmWanMbusF5VIF13		OBJECT-TYPE
			SYNTAX	INTEGER
			MAX-ACCESS	read-only
			STATUS	current
			::= { hmWanMbusF5 44 }

hmWanMbusF5Value13		OBJECT-TYPE
			SYNTAX	INTEGER
			MAX-ACCESS	read-only
			STATUS	current
			::= { hmWanMbusF5 45 }

hmWanMbusF5VIF14		OBJECT-TYPE
			SYNTAX	INTEGER
			MAX-ACCESS	read-only
			STATUS	current
			::= { hmWanMbusF5 46 }

hmWanMbusF5Value14		OBJECT-TYPE
			SYNTAX	INTEGER
			MAX-ACCESS	read-only
			STATUS	current
			::= { hmWanMbusF5 47 }

hmWanMbusF5VIF15		OBJECT-TYPE
			SYNTAX	INTEGER
			MAX-ACCESS	read-only
			STATUS	current
			::= { hmWanMbusF5 48 }

hmWanMbusF5Value15		OBJECT-TYPE
			SYNTAX	INTEGER
			MAX-ACCESS	read-only
			STATUS	current
			::= { hmWanMbusF5 49 }

hmWanMbusF5VIF16		OBJECT-TYPE
			SYNTAX	INTEGER
			MAX-ACCESS	read-only
			STATUS	current
			::= { hmWanMbusF5 50 }

hmWanMbusF5Value16		OBJECT-TYPE
			SYNTAX	INTEGER
			MAX-ACCESS	read-only
			STATUS	current
			::= { hmWanMbusF5 51 }

hmWanMbusF5VIF17		OBJECT-TYPE
			SYNTAX	INTEGER
			MAX-ACCESS	read-only
			STATUS	current
			::= { hmWanMbusF5 52 }

hmWanMbusF5Value17		OBJECT-TYPE
			SYNTAX	INTEGER
			MAX-ACCESS	read-only
			STATUS	current
			::= { hmWanMbusF5 53 }

hmWanMbusF5VIF18		OBJECT-TYPE
			SYNTAX	INTEGER
			MAX-ACCESS	read-only
			STATUS	current
			::= { hmWanMbusF5 54 }

hmWanMbusF5Value18		OBJECT-TYPE
			SYNTAX	INTEGER
			MAX-ACCESS	read-only
			STATUS	current
			::= { hmWanMbusF5 55 }

hmWanMbusF5VIF19		OBJECT-TYPE
			SYNTAX	INTEGER
			MAX-ACCESS	read-only
			STATUS	current
			::= { hmWanMbusF5 56 }

hmWanMbusF5Value19		OBJECT-TYPE
			SYNTAX	INTEGER
			MAX-ACCESS	read-only
			STATUS	current
			::= { hmWanMbusF5 57 }

hmWanMbusF5VIF1A		OBJECT-TYPE
			SYNTAX	INTEGER
			MAX-ACCESS	read-only
			STATUS	current
			::= { hmWanMbusF5 58 }

hmWanMbusF5Value1A		OBJECT-TYPE
			SYNTAX	INTEGER
			MAX-ACCESS	read-only
			STATUS	current
			::= { hmWanMbusF5 59 }

hmWanMbusF5VIF1B		OBJECT-TYPE
			SYNTAX	INTEGER
			MAX-ACCESS	read-only
			STATUS	current
			::= { hmWanMbusF5 60 }

hmWanMbusF5Value1B		OBJECT-TYPE
			SYNTAX	INTEGER
			MAX-ACCESS	read-only
			STATUS	current
			::= { hmWanMbusF5 61 }

hmWanMbusF5VIF1C		OBJECT-TYPE
			SYNTAX	INTEGER
			MAX-ACCESS	read-only
			STATUS	current
			::= { hmWanMbusF5 62 }

hmWanMbusF5Value1C		OBJECT-TYPE
			SYNTAX	INTEGER
			MAX-ACCESS	read-only
			STATUS	current
			::= { hmWanMbusF5 63 }

hmWanMbusF5VIF1D		OBJECT-TYPE
			SYNTAX	INTEGER
			MAX-ACCESS	read-only
			STATUS	current
			::= { hmWanMbusF5 64 }

hmWanMbusF5Value1D		OBJECT-TYPE
			SYNTAX	INTEGER
			MAX-ACCESS	read-only
			STATUS	current
			::= { hmWanMbusF5 65 }

hmWanMbusF5VIF1E		OBJECT-TYPE
			SYNTAX	INTEGER
			MAX-ACCESS	read-only
			STATUS	current
			::= { hmWanMbusF5 66 }

hmWanMbusF5Value1E		OBJECT-TYPE
			SYNTAX	INTEGER
			MAX-ACCESS	read-only
			STATUS	current
			::= { hmWanMbusF5 67 }

hmWanMbusF5VIF1F		OBJECT-TYPE
			SYNTAX	INTEGER
			MAX-ACCESS	read-only
			STATUS	current
			::= { hmWanMbusF5 68 }

hmWanMbusF5Value1F		OBJECT-TYPE
			SYNTAX	INTEGER
			MAX-ACCESS	read-only
			STATUS	current
			::= { hmWanMbusF5 69 }

hmWanMbusF5VIF20		OBJECT-TYPE
			SYNTAX	INTEGER
			MAX-ACCESS	read-only
			STATUS	current
			::= { hmWanMbusF5 70 }

hmWanMbusF5Value20		OBJECT-TYPE
			SYNTAX	INTEGER
			MAX-ACCESS	read-only
			STATUS	current
			::= { hmWanMbusF5 71 }

hmWanMbusF5VIF21		OBJECT-TYPE
			SYNTAX	INTEGER
			MAX-ACCESS	read-only
			STATUS	current
			::= { hmWanMbusF5 72 }

hmWanMbusF5Value21		OBJECT-TYPE
			SYNTAX	INTEGER
			MAX-ACCESS	read-only
			STATUS	current
			::= { hmWanMbusF5 73 }

hmWanMbusF5VIF22		OBJECT-TYPE
			SYNTAX	INTEGER
			MAX-ACCESS	read-only
			STATUS	current
			::= { hmWanMbusF5 74 }

hmWanMbusF5Value22		OBJECT-TYPE
			SYNTAX	INTEGER
			MAX-ACCESS	read-only
			STATUS	current
			::= { hmWanMbusF5 75 }

hmWanMbusF5VIF23		OBJECT-TYPE
			SYNTAX	INTEGER
			MAX-ACCESS	read-only
			STATUS	current
			::= { hmWanMbusF5 76 }

hmWanMbusF5Value23		OBJECT-TYPE
			SYNTAX	INTEGER
			MAX-ACCESS	read-only
			STATUS	current
			::= { hmWanMbusF5 77 }

hmWanMbusF5VIF24		OBJECT-TYPE
			SYNTAX	INTEGER
			MAX-ACCESS	read-only
			STATUS	current
			::= { hmWanMbusF5 78 }

hmWanMbusF5Value24		OBJECT-TYPE
			SYNTAX	INTEGER
			MAX-ACCESS	read-only
			STATUS	current
			::= { hmWanMbusF5 79 }

hmWanMbusF5VIF25		OBJECT-TYPE
			SYNTAX	INTEGER
			MAX-ACCESS	read-only
			STATUS	current
			::= { hmWanMbusF5 80 }

hmWanMbusF5Value25		OBJECT-TYPE
			SYNTAX	INTEGER
			MAX-ACCESS	read-only
			STATUS	current
			::= { hmWanMbusF5 81 }

hmWanMbusF5VIF26		OBJECT-TYPE
			SYNTAX	INTEGER
			MAX-ACCESS	read-only
			STATUS	current
			::= { hmWanMbusF5 82 }

hmWanMbusF5Value26		OBJECT-TYPE
			SYNTAX	INTEGER
			MAX-ACCESS	read-only
			STATUS	current
			::= { hmWanMbusF5 83 }

hmWanMbusF5VIF27		OBJECT-TYPE
			SYNTAX	INTEGER
			MAX-ACCESS	read-only
			STATUS	current
			::= { hmWanMbusF5 84 }

hmWanMbusF5Value27		OBJECT-TYPE
			SYNTAX	INTEGER
			MAX-ACCESS	read-only
			STATUS	current
			::= { hmWanMbusF5 85 }

hmWanMbusF5VIF28		OBJECT-TYPE
			SYNTAX	INTEGER
			MAX-ACCESS	read-only
			STATUS	current
			::= { hmWanMbusF5 86 }

hmWanMbusF5Value28		OBJECT-TYPE
			SYNTAX	INTEGER
			MAX-ACCESS	read-only
			STATUS	current
			::= { hmWanMbusF5 87 }

hmWanMbusF5VIF29		OBJECT-TYPE
			SYNTAX	INTEGER
			MAX-ACCESS	read-only
			STATUS	current
			::= { hmWanMbusF5 88 }

hmWanMbusF5Value29		OBJECT-TYPE
			SYNTAX	INTEGER
			MAX-ACCESS	read-only
			STATUS	current
			::= { hmWanMbusF5 89 }

hmWanMbusF5VIF2A		OBJECT-TYPE
			SYNTAX	INTEGER
			MAX-ACCESS	read-only
			STATUS	current
			::= { hmWanMbusF5 90 }

hmWanMbusF5Value2A		OBJECT-TYPE
			SYNTAX	INTEGER
			MAX-ACCESS	read-only
			STATUS	current
			::= { hmWanMbusF5 91 }

hmWanMbusF5VIF2B		OBJECT-TYPE
			SYNTAX	INTEGER
			MAX-ACCESS	read-only
			STATUS	current
			::= { hmWanMbusF5 92 }

hmWanMbusF5Value2B		OBJECT-TYPE
			SYNTAX	INTEGER
			MAX-ACCESS	read-only
			STATUS	current
			::= { hmWanMbusF5 93 }

hmWanMbusF5VIF2C		OBJECT-TYPE
			SYNTAX	INTEGER
			MAX-ACCESS	read-only
			STATUS	current
			::= { hmWanMbusF5 94 }

hmWanMbusF5Value2C		OBJECT-TYPE
			SYNTAX	INTEGER
			MAX-ACCESS	read-only
			STATUS	current
			::= { hmWanMbusF5 95 }

hmWanMbusF5VIF2D		OBJECT-TYPE
			SYNTAX	INTEGER
			MAX-ACCESS	read-only
			STATUS	current
			::= { hmWanMbusF5 96 }

hmWanMbusF5Value2D		OBJECT-TYPE
			SYNTAX	INTEGER
			MAX-ACCESS	read-only
			STATUS	current
			::= { hmWanMbusF5 97 }

hmWanMbusF5VIF2E		OBJECT-TYPE
			SYNTAX	INTEGER
			MAX-ACCESS	read-only
			STATUS	current
			::= { hmWanMbusF5 98 }

hmWanMbusF5Value2E		OBJECT-TYPE
			SYNTAX	INTEGER
			MAX-ACCESS	read-only
			STATUS	current
			::= { hmWanMbusF5 99 }

hmWanMbusF5VIF2F		OBJECT-TYPE
			SYNTAX	INTEGER
			MAX-ACCESS	read-only
			STATUS	current
			::= { hmWanMbusF5 100 }

hmWanMbusF5Value2F		OBJECT-TYPE
			SYNTAX	INTEGER
			MAX-ACCESS	read-only
			STATUS	current
			::= { hmWanMbusF5 101 }

hmWanMbusF6			OBJECT IDENTIFIER ::= { hmWanMbus 246 }

hmWanMbusF6IdNumber		OBJECT-TYPE
			SYNTAX	Gauge32
			MAX-ACCESS	read-only
			STATUS	current
			::= { hmWanMbusF6 1 }

hmWanMbusF6Manufacturer	OBJECT-TYPE
			SYNTAX	Gauge32
			MAX-ACCESS	read-only
			STATUS	current
			::= { hmWanMbusF6 2 }

hmWanMbusF6Version		OBJECT-TYPE
			SYNTAX	Gauge32
			MAX-ACCESS	read-only
			STATUS	current
			::= { hmWanMbusF6 3 }

hmWanMbusF6Medium		OBJECT-TYPE
			SYNTAX	Gauge32
			MAX-ACCESS	read-only
			STATUS	current
			::= { hmWanMbusF6 4 }

hmWanMbusF6Status		OBJECT-TYPE
			SYNTAX	Gauge32
			MAX-ACCESS	read-only
			STATUS	current
			::= { hmWanMbusF6 5 }

hmWanMbusF6VIF00		OBJECT-TYPE
			SYNTAX	INTEGER
			MAX-ACCESS	read-only
			STATUS	current
			::= { hmWanMbusF6 6 }

hmWanMbusF6Value00		OBJECT-TYPE
			SYNTAX	INTEGER
			MAX-ACCESS	read-only
			STATUS	current
			::= { hmWanMbusF6 7 }

hmWanMbusF6VIF01		OBJECT-TYPE
			SYNTAX	INTEGER
			MAX-ACCESS	read-only
			STATUS	current
			::= { hmWanMbusF6 8 }

hmWanMbusF6Value01		OBJECT-TYPE
			SYNTAX	INTEGER
			MAX-ACCESS	read-only
			STATUS	current
			::= { hmWanMbusF6 9 }

hmWanMbusF6VIF02		OBJECT-TYPE
			SYNTAX	INTEGER
			MAX-ACCESS	read-only
			STATUS	current
			::= { hmWanMbusF6 10 }

hmWanMbusF6Value02		OBJECT-TYPE
			SYNTAX	INTEGER
			MAX-ACCESS	read-only
			STATUS	current
			::= { hmWanMbusF6 11 }

hmWanMbusF6VIF03		OBJECT-TYPE
			SYNTAX	INTEGER
			MAX-ACCESS	read-only
			STATUS	current
			::= { hmWanMbusF6 12 }

hmWanMbusF6Value03		OBJECT-TYPE
			SYNTAX	INTEGER
			MAX-ACCESS	read-only
			STATUS	current
			::= { hmWanMbusF6 13 }

hmWanMbusF6VIF04		OBJECT-TYPE
			SYNTAX	INTEGER
			MAX-ACCESS	read-only
			STATUS	current
			::= { hmWanMbusF6 14 }

hmWanMbusF6Value04		OBJECT-TYPE
			SYNTAX	INTEGER
			MAX-ACCESS	read-only
			STATUS	current
			::= { hmWanMbusF6 15 }

hmWanMbusF6VIF05		OBJECT-TYPE
			SYNTAX	INTEGER
			MAX-ACCESS	read-only
			STATUS	current
			::= { hmWanMbusF6 16 }

hmWanMbusF6Value05		OBJECT-TYPE
			SYNTAX	INTEGER
			MAX-ACCESS	read-only
			STATUS	current
			::= { hmWanMbusF6 17 }

hmWanMbusF6VIF06		OBJECT-TYPE
			SYNTAX	INTEGER
			MAX-ACCESS	read-only
			STATUS	current
			::= { hmWanMbusF6 18 }

hmWanMbusF6Value06		OBJECT-TYPE
			SYNTAX	INTEGER
			MAX-ACCESS	read-only
			STATUS	current
			::= { hmWanMbusF6 19 }

hmWanMbusF6VIF07		OBJECT-TYPE
			SYNTAX	INTEGER
			MAX-ACCESS	read-only
			STATUS	current
			::= { hmWanMbusF6 20 }

hmWanMbusF6Value07		OBJECT-TYPE
			SYNTAX	INTEGER
			MAX-ACCESS	read-only
			STATUS	current
			::= { hmWanMbusF6 21 }

hmWanMbusF6VIF08		OBJECT-TYPE
			SYNTAX	INTEGER
			MAX-ACCESS	read-only
			STATUS	current
			::= { hmWanMbusF6 22 }

hmWanMbusF6Value08		OBJECT-TYPE
			SYNTAX	INTEGER
			MAX-ACCESS	read-only
			STATUS	current
			::= { hmWanMbusF6 23 }

hmWanMbusF6VIF09		OBJECT-TYPE
			SYNTAX	INTEGER
			MAX-ACCESS	read-only
			STATUS	current
			::= { hmWanMbusF6 24 }

hmWanMbusF6Value09		OBJECT-TYPE
			SYNTAX	INTEGER
			MAX-ACCESS	read-only
			STATUS	current
			::= { hmWanMbusF6 25 }

hmWanMbusF6VIF0A		OBJECT-TYPE
			SYNTAX	INTEGER
			MAX-ACCESS	read-only
			STATUS	current
			::= { hmWanMbusF6 26 }

hmWanMbusF6Value0A		OBJECT-TYPE
			SYNTAX	INTEGER
			MAX-ACCESS	read-only
			STATUS	current
			::= { hmWanMbusF6 27 }

hmWanMbusF6VIF0B		OBJECT-TYPE
			SYNTAX	INTEGER
			MAX-ACCESS	read-only
			STATUS	current
			::= { hmWanMbusF6 28 }

hmWanMbusF6Value0B		OBJECT-TYPE
			SYNTAX	INTEGER
			MAX-ACCESS	read-only
			STATUS	current
			::= { hmWanMbusF6 29 }

hmWanMbusF6VIF0C		OBJECT-TYPE
			SYNTAX	INTEGER
			MAX-ACCESS	read-only
			STATUS	current
			::= { hmWanMbusF6 30 }

hmWanMbusF6Value0C		OBJECT-TYPE
			SYNTAX	INTEGER
			MAX-ACCESS	read-only
			STATUS	current
			::= { hmWanMbusF6 31 }

hmWanMbusF6VIF0D		OBJECT-TYPE
			SYNTAX	INTEGER
			MAX-ACCESS	read-only
			STATUS	current
			::= { hmWanMbusF6 32 }

hmWanMbusF6Value0D		OBJECT-TYPE
			SYNTAX	INTEGER
			MAX-ACCESS	read-only
			STATUS	current
			::= { hmWanMbusF6 33 }

hmWanMbusF6VIF0E		OBJECT-TYPE
			SYNTAX	INTEGER
			MAX-ACCESS	read-only
			STATUS	current
			::= { hmWanMbusF6 34 }

hmWanMbusF6Value0E		OBJECT-TYPE
			SYNTAX	INTEGER
			MAX-ACCESS	read-only
			STATUS	current
			::= { hmWanMbusF6 35 }

hmWanMbusF6VIF0F		OBJECT-TYPE
			SYNTAX	INTEGER
			MAX-ACCESS	read-only
			STATUS	current
			::= { hmWanMbusF6 36 }

hmWanMbusF6Value0F		OBJECT-TYPE
			SYNTAX	INTEGER
			MAX-ACCESS	read-only
			STATUS	current
			::= { hmWanMbusF6 37 }

hmWanMbusF6VIF10		OBJECT-TYPE
			SYNTAX	INTEGER
			MAX-ACCESS	read-only
			STATUS	current
			::= { hmWanMbusF6 38 }

hmWanMbusF6Value10		OBJECT-TYPE
			SYNTAX	INTEGER
			MAX-ACCESS	read-only
			STATUS	current
			::= { hmWanMbusF6 39 }

hmWanMbusF6VIF11		OBJECT-TYPE
			SYNTAX	INTEGER
			MAX-ACCESS	read-only
			STATUS	current
			::= { hmWanMbusF6 40 }

hmWanMbusF6Value11		OBJECT-TYPE
			SYNTAX	INTEGER
			MAX-ACCESS	read-only
			STATUS	current
			::= { hmWanMbusF6 41 }

hmWanMbusF6VIF12		OBJECT-TYPE
			SYNTAX	INTEGER
			MAX-ACCESS	read-only
			STATUS	current
			::= { hmWanMbusF6 42 }

hmWanMbusF6Value12		OBJECT-TYPE
			SYNTAX	INTEGER
			MAX-ACCESS	read-only
			STATUS	current
			::= { hmWanMbusF6 43 }

hmWanMbusF6VIF13		OBJECT-TYPE
			SYNTAX	INTEGER
			MAX-ACCESS	read-only
			STATUS	current
			::= { hmWanMbusF6 44 }

hmWanMbusF6Value13		OBJECT-TYPE
			SYNTAX	INTEGER
			MAX-ACCESS	read-only
			STATUS	current
			::= { hmWanMbusF6 45 }

hmWanMbusF6VIF14		OBJECT-TYPE
			SYNTAX	INTEGER
			MAX-ACCESS	read-only
			STATUS	current
			::= { hmWanMbusF6 46 }

hmWanMbusF6Value14		OBJECT-TYPE
			SYNTAX	INTEGER
			MAX-ACCESS	read-only
			STATUS	current
			::= { hmWanMbusF6 47 }

hmWanMbusF6VIF15		OBJECT-TYPE
			SYNTAX	INTEGER
			MAX-ACCESS	read-only
			STATUS	current
			::= { hmWanMbusF6 48 }

hmWanMbusF6Value15		OBJECT-TYPE
			SYNTAX	INTEGER
			MAX-ACCESS	read-only
			STATUS	current
			::= { hmWanMbusF6 49 }

hmWanMbusF6VIF16		OBJECT-TYPE
			SYNTAX	INTEGER
			MAX-ACCESS	read-only
			STATUS	current
			::= { hmWanMbusF6 50 }

hmWanMbusF6Value16		OBJECT-TYPE
			SYNTAX	INTEGER
			MAX-ACCESS	read-only
			STATUS	current
			::= { hmWanMbusF6 51 }

hmWanMbusF6VIF17		OBJECT-TYPE
			SYNTAX	INTEGER
			MAX-ACCESS	read-only
			STATUS	current
			::= { hmWanMbusF6 52 }

hmWanMbusF6Value17		OBJECT-TYPE
			SYNTAX	INTEGER
			MAX-ACCESS	read-only
			STATUS	current
			::= { hmWanMbusF6 53 }

hmWanMbusF6VIF18		OBJECT-TYPE
			SYNTAX	INTEGER
			MAX-ACCESS	read-only
			STATUS	current
			::= { hmWanMbusF6 54 }

hmWanMbusF6Value18		OBJECT-TYPE
			SYNTAX	INTEGER
			MAX-ACCESS	read-only
			STATUS	current
			::= { hmWanMbusF6 55 }

hmWanMbusF6VIF19		OBJECT-TYPE
			SYNTAX	INTEGER
			MAX-ACCESS	read-only
			STATUS	current
			::= { hmWanMbusF6 56 }

hmWanMbusF6Value19		OBJECT-TYPE
			SYNTAX	INTEGER
			MAX-ACCESS	read-only
			STATUS	current
			::= { hmWanMbusF6 57 }

hmWanMbusF6VIF1A		OBJECT-TYPE
			SYNTAX	INTEGER
			MAX-ACCESS	read-only
			STATUS	current
			::= { hmWanMbusF6 58 }

hmWanMbusF6Value1A		OBJECT-TYPE
			SYNTAX	INTEGER
			MAX-ACCESS	read-only
			STATUS	current
			::= { hmWanMbusF6 59 }

hmWanMbusF6VIF1B		OBJECT-TYPE
			SYNTAX	INTEGER
			MAX-ACCESS	read-only
			STATUS	current
			::= { hmWanMbusF6 60 }

hmWanMbusF6Value1B		OBJECT-TYPE
			SYNTAX	INTEGER
			MAX-ACCESS	read-only
			STATUS	current
			::= { hmWanMbusF6 61 }

hmWanMbusF6VIF1C		OBJECT-TYPE
			SYNTAX	INTEGER
			MAX-ACCESS	read-only
			STATUS	current
			::= { hmWanMbusF6 62 }

hmWanMbusF6Value1C		OBJECT-TYPE
			SYNTAX	INTEGER
			MAX-ACCESS	read-only
			STATUS	current
			::= { hmWanMbusF6 63 }

hmWanMbusF6VIF1D		OBJECT-TYPE
			SYNTAX	INTEGER
			MAX-ACCESS	read-only
			STATUS	current
			::= { hmWanMbusF6 64 }

hmWanMbusF6Value1D		OBJECT-TYPE
			SYNTAX	INTEGER
			MAX-ACCESS	read-only
			STATUS	current
			::= { hmWanMbusF6 65 }

hmWanMbusF6VIF1E		OBJECT-TYPE
			SYNTAX	INTEGER
			MAX-ACCESS	read-only
			STATUS	current
			::= { hmWanMbusF6 66 }

hmWanMbusF6Value1E		OBJECT-TYPE
			SYNTAX	INTEGER
			MAX-ACCESS	read-only
			STATUS	current
			::= { hmWanMbusF6 67 }

hmWanMbusF6VIF1F		OBJECT-TYPE
			SYNTAX	INTEGER
			MAX-ACCESS	read-only
			STATUS	current
			::= { hmWanMbusF6 68 }

hmWanMbusF6Value1F		OBJECT-TYPE
			SYNTAX	INTEGER
			MAX-ACCESS	read-only
			STATUS	current
			::= { hmWanMbusF6 69 }

hmWanMbusF6VIF20		OBJECT-TYPE
			SYNTAX	INTEGER
			MAX-ACCESS	read-only
			STATUS	current
			::= { hmWanMbusF6 70 }

hmWanMbusF6Value20		OBJECT-TYPE
			SYNTAX	INTEGER
			MAX-ACCESS	read-only
			STATUS	current
			::= { hmWanMbusF6 71 }

hmWanMbusF6VIF21		OBJECT-TYPE
			SYNTAX	INTEGER
			MAX-ACCESS	read-only
			STATUS	current
			::= { hmWanMbusF6 72 }

hmWanMbusF6Value21		OBJECT-TYPE
			SYNTAX	INTEGER
			MAX-ACCESS	read-only
			STATUS	current
			::= { hmWanMbusF6 73 }

hmWanMbusF6VIF22		OBJECT-TYPE
			SYNTAX	INTEGER
			MAX-ACCESS	read-only
			STATUS	current
			::= { hmWanMbusF6 74 }

hmWanMbusF6Value22		OBJECT-TYPE
			SYNTAX	INTEGER
			MAX-ACCESS	read-only
			STATUS	current
			::= { hmWanMbusF6 75 }

hmWanMbusF6VIF23		OBJECT-TYPE
			SYNTAX	INTEGER
			MAX-ACCESS	read-only
			STATUS	current
			::= { hmWanMbusF6 76 }

hmWanMbusF6Value23		OBJECT-TYPE
			SYNTAX	INTEGER
			MAX-ACCESS	read-only
			STATUS	current
			::= { hmWanMbusF6 77 }

hmWanMbusF6VIF24		OBJECT-TYPE
			SYNTAX	INTEGER
			MAX-ACCESS	read-only
			STATUS	current
			::= { hmWanMbusF6 78 }

hmWanMbusF6Value24		OBJECT-TYPE
			SYNTAX	INTEGER
			MAX-ACCESS	read-only
			STATUS	current
			::= { hmWanMbusF6 79 }

hmWanMbusF6VIF25		OBJECT-TYPE
			SYNTAX	INTEGER
			MAX-ACCESS	read-only
			STATUS	current
			::= { hmWanMbusF6 80 }

hmWanMbusF6Value25		OBJECT-TYPE
			SYNTAX	INTEGER
			MAX-ACCESS	read-only
			STATUS	current
			::= { hmWanMbusF6 81 }

hmWanMbusF6VIF26		OBJECT-TYPE
			SYNTAX	INTEGER
			MAX-ACCESS	read-only
			STATUS	current
			::= { hmWanMbusF6 82 }

hmWanMbusF6Value26		OBJECT-TYPE
			SYNTAX	INTEGER
			MAX-ACCESS	read-only
			STATUS	current
			::= { hmWanMbusF6 83 }

hmWanMbusF6VIF27		OBJECT-TYPE
			SYNTAX	INTEGER
			MAX-ACCESS	read-only
			STATUS	current
			::= { hmWanMbusF6 84 }

hmWanMbusF6Value27		OBJECT-TYPE
			SYNTAX	INTEGER
			MAX-ACCESS	read-only
			STATUS	current
			::= { hmWanMbusF6 85 }

hmWanMbusF6VIF28		OBJECT-TYPE
			SYNTAX	INTEGER
			MAX-ACCESS	read-only
			STATUS	current
			::= { hmWanMbusF6 86 }

hmWanMbusF6Value28		OBJECT-TYPE
			SYNTAX	INTEGER
			MAX-ACCESS	read-only
			STATUS	current
			::= { hmWanMbusF6 87 }

hmWanMbusF6VIF29		OBJECT-TYPE
			SYNTAX	INTEGER
			MAX-ACCESS	read-only
			STATUS	current
			::= { hmWanMbusF6 88 }

hmWanMbusF6Value29		OBJECT-TYPE
			SYNTAX	INTEGER
			MAX-ACCESS	read-only
			STATUS	current
			::= { hmWanMbusF6 89 }

hmWanMbusF6VIF2A		OBJECT-TYPE
			SYNTAX	INTEGER
			MAX-ACCESS	read-only
			STATUS	current
			::= { hmWanMbusF6 90 }

hmWanMbusF6Value2A		OBJECT-TYPE
			SYNTAX	INTEGER
			MAX-ACCESS	read-only
			STATUS	current
			::= { hmWanMbusF6 91 }

hmWanMbusF6VIF2B		OBJECT-TYPE
			SYNTAX	INTEGER
			MAX-ACCESS	read-only
			STATUS	current
			::= { hmWanMbusF6 92 }

hmWanMbusF6Value2B		OBJECT-TYPE
			SYNTAX	INTEGER
			MAX-ACCESS	read-only
			STATUS	current
			::= { hmWanMbusF6 93 }

hmWanMbusF6VIF2C		OBJECT-TYPE
			SYNTAX	INTEGER
			MAX-ACCESS	read-only
			STATUS	current
			::= { hmWanMbusF6 94 }

hmWanMbusF6Value2C		OBJECT-TYPE
			SYNTAX	INTEGER
			MAX-ACCESS	read-only
			STATUS	current
			::= { hmWanMbusF6 95 }

hmWanMbusF6VIF2D		OBJECT-TYPE
			SYNTAX	INTEGER
			MAX-ACCESS	read-only
			STATUS	current
			::= { hmWanMbusF6 96 }

hmWanMbusF6Value2D		OBJECT-TYPE
			SYNTAX	INTEGER
			MAX-ACCESS	read-only
			STATUS	current
			::= { hmWanMbusF6 97 }

hmWanMbusF6VIF2E		OBJECT-TYPE
			SYNTAX	INTEGER
			MAX-ACCESS	read-only
			STATUS	current
			::= { hmWanMbusF6 98 }

hmWanMbusF6Value2E		OBJECT-TYPE
			SYNTAX	INTEGER
			MAX-ACCESS	read-only
			STATUS	current
			::= { hmWanMbusF6 99 }

hmWanMbusF6VIF2F		OBJECT-TYPE
			SYNTAX	INTEGER
			MAX-ACCESS	read-only
			STATUS	current
			::= { hmWanMbusF6 100 }

hmWanMbusF6Value2F		OBJECT-TYPE
			SYNTAX	INTEGER
			MAX-ACCESS	read-only
			STATUS	current
			::= { hmWanMbusF6 101 }

hmWanMbusF7			OBJECT IDENTIFIER ::= { hmWanMbus 247 }

hmWanMbusF7IdNumber		OBJECT-TYPE
			SYNTAX	Gauge32
			MAX-ACCESS	read-only
			STATUS	current
			::= { hmWanMbusF7 1 }

hmWanMbusF7Manufacturer	OBJECT-TYPE
			SYNTAX	Gauge32
			MAX-ACCESS	read-only
			STATUS	current
			::= { hmWanMbusF7 2 }

hmWanMbusF7Version		OBJECT-TYPE
			SYNTAX	Gauge32
			MAX-ACCESS	read-only
			STATUS	current
			::= { hmWanMbusF7 3 }

hmWanMbusF7Medium		OBJECT-TYPE
			SYNTAX	Gauge32
			MAX-ACCESS	read-only
			STATUS	current
			::= { hmWanMbusF7 4 }

hmWanMbusF7Status		OBJECT-TYPE
			SYNTAX	Gauge32
			MAX-ACCESS	read-only
			STATUS	current
			::= { hmWanMbusF7 5 }

hmWanMbusF7VIF00		OBJECT-TYPE
			SYNTAX	INTEGER
			MAX-ACCESS	read-only
			STATUS	current
			::= { hmWanMbusF7 6 }

hmWanMbusF7Value00		OBJECT-TYPE
			SYNTAX	INTEGER
			MAX-ACCESS	read-only
			STATUS	current
			::= { hmWanMbusF7 7 }

hmWanMbusF7VIF01		OBJECT-TYPE
			SYNTAX	INTEGER
			MAX-ACCESS	read-only
			STATUS	current
			::= { hmWanMbusF7 8 }

hmWanMbusF7Value01		OBJECT-TYPE
			SYNTAX	INTEGER
			MAX-ACCESS	read-only
			STATUS	current
			::= { hmWanMbusF7 9 }

hmWanMbusF7VIF02		OBJECT-TYPE
			SYNTAX	INTEGER
			MAX-ACCESS	read-only
			STATUS	current
			::= { hmWanMbusF7 10 }

hmWanMbusF7Value02		OBJECT-TYPE
			SYNTAX	INTEGER
			MAX-ACCESS	read-only
			STATUS	current
			::= { hmWanMbusF7 11 }

hmWanMbusF7VIF03		OBJECT-TYPE
			SYNTAX	INTEGER
			MAX-ACCESS	read-only
			STATUS	current
			::= { hmWanMbusF7 12 }

hmWanMbusF7Value03		OBJECT-TYPE
			SYNTAX	INTEGER
			MAX-ACCESS	read-only
			STATUS	current
			::= { hmWanMbusF7 13 }

hmWanMbusF7VIF04		OBJECT-TYPE
			SYNTAX	INTEGER
			MAX-ACCESS	read-only
			STATUS	current
			::= { hmWanMbusF7 14 }

hmWanMbusF7Value04		OBJECT-TYPE
			SYNTAX	INTEGER
			MAX-ACCESS	read-only
			STATUS	current
			::= { hmWanMbusF7 15 }

hmWanMbusF7VIF05		OBJECT-TYPE
			SYNTAX	INTEGER
			MAX-ACCESS	read-only
			STATUS	current
			::= { hmWanMbusF7 16 }

hmWanMbusF7Value05		OBJECT-TYPE
			SYNTAX	INTEGER
			MAX-ACCESS	read-only
			STATUS	current
			::= { hmWanMbusF7 17 }

hmWanMbusF7VIF06		OBJECT-TYPE
			SYNTAX	INTEGER
			MAX-ACCESS	read-only
			STATUS	current
			::= { hmWanMbusF7 18 }

hmWanMbusF7Value06		OBJECT-TYPE
			SYNTAX	INTEGER
			MAX-ACCESS	read-only
			STATUS	current
			::= { hmWanMbusF7 19 }

hmWanMbusF7VIF07		OBJECT-TYPE
			SYNTAX	INTEGER
			MAX-ACCESS	read-only
			STATUS	current
			::= { hmWanMbusF7 20 }

hmWanMbusF7Value07		OBJECT-TYPE
			SYNTAX	INTEGER
			MAX-ACCESS	read-only
			STATUS	current
			::= { hmWanMbusF7 21 }

hmWanMbusF7VIF08		OBJECT-TYPE
			SYNTAX	INTEGER
			MAX-ACCESS	read-only
			STATUS	current
			::= { hmWanMbusF7 22 }

hmWanMbusF7Value08		OBJECT-TYPE
			SYNTAX	INTEGER
			MAX-ACCESS	read-only
			STATUS	current
			::= { hmWanMbusF7 23 }

hmWanMbusF7VIF09		OBJECT-TYPE
			SYNTAX	INTEGER
			MAX-ACCESS	read-only
			STATUS	current
			::= { hmWanMbusF7 24 }

hmWanMbusF7Value09		OBJECT-TYPE
			SYNTAX	INTEGER
			MAX-ACCESS	read-only
			STATUS	current
			::= { hmWanMbusF7 25 }

hmWanMbusF7VIF0A		OBJECT-TYPE
			SYNTAX	INTEGER
			MAX-ACCESS	read-only
			STATUS	current
			::= { hmWanMbusF7 26 }

hmWanMbusF7Value0A		OBJECT-TYPE
			SYNTAX	INTEGER
			MAX-ACCESS	read-only
			STATUS	current
			::= { hmWanMbusF7 27 }

hmWanMbusF7VIF0B		OBJECT-TYPE
			SYNTAX	INTEGER
			MAX-ACCESS	read-only
			STATUS	current
			::= { hmWanMbusF7 28 }

hmWanMbusF7Value0B		OBJECT-TYPE
			SYNTAX	INTEGER
			MAX-ACCESS	read-only
			STATUS	current
			::= { hmWanMbusF7 29 }

hmWanMbusF7VIF0C		OBJECT-TYPE
			SYNTAX	INTEGER
			MAX-ACCESS	read-only
			STATUS	current
			::= { hmWanMbusF7 30 }

hmWanMbusF7Value0C		OBJECT-TYPE
			SYNTAX	INTEGER
			MAX-ACCESS	read-only
			STATUS	current
			::= { hmWanMbusF7 31 }

hmWanMbusF7VIF0D		OBJECT-TYPE
			SYNTAX	INTEGER
			MAX-ACCESS	read-only
			STATUS	current
			::= { hmWanMbusF7 32 }

hmWanMbusF7Value0D		OBJECT-TYPE
			SYNTAX	INTEGER
			MAX-ACCESS	read-only
			STATUS	current
			::= { hmWanMbusF7 33 }

hmWanMbusF7VIF0E		OBJECT-TYPE
			SYNTAX	INTEGER
			MAX-ACCESS	read-only
			STATUS	current
			::= { hmWanMbusF7 34 }

hmWanMbusF7Value0E		OBJECT-TYPE
			SYNTAX	INTEGER
			MAX-ACCESS	read-only
			STATUS	current
			::= { hmWanMbusF7 35 }

hmWanMbusF7VIF0F		OBJECT-TYPE
			SYNTAX	INTEGER
			MAX-ACCESS	read-only
			STATUS	current
			::= { hmWanMbusF7 36 }

hmWanMbusF7Value0F		OBJECT-TYPE
			SYNTAX	INTEGER
			MAX-ACCESS	read-only
			STATUS	current
			::= { hmWanMbusF7 37 }

hmWanMbusF7VIF10		OBJECT-TYPE
			SYNTAX	INTEGER
			MAX-ACCESS	read-only
			STATUS	current
			::= { hmWanMbusF7 38 }

hmWanMbusF7Value10		OBJECT-TYPE
			SYNTAX	INTEGER
			MAX-ACCESS	read-only
			STATUS	current
			::= { hmWanMbusF7 39 }

hmWanMbusF7VIF11		OBJECT-TYPE
			SYNTAX	INTEGER
			MAX-ACCESS	read-only
			STATUS	current
			::= { hmWanMbusF7 40 }

hmWanMbusF7Value11		OBJECT-TYPE
			SYNTAX	INTEGER
			MAX-ACCESS	read-only
			STATUS	current
			::= { hmWanMbusF7 41 }

hmWanMbusF7VIF12		OBJECT-TYPE
			SYNTAX	INTEGER
			MAX-ACCESS	read-only
			STATUS	current
			::= { hmWanMbusF7 42 }

hmWanMbusF7Value12		OBJECT-TYPE
			SYNTAX	INTEGER
			MAX-ACCESS	read-only
			STATUS	current
			::= { hmWanMbusF7 43 }

hmWanMbusF7VIF13		OBJECT-TYPE
			SYNTAX	INTEGER
			MAX-ACCESS	read-only
			STATUS	current
			::= { hmWanMbusF7 44 }

hmWanMbusF7Value13		OBJECT-TYPE
			SYNTAX	INTEGER
			MAX-ACCESS	read-only
			STATUS	current
			::= { hmWanMbusF7 45 }

hmWanMbusF7VIF14		OBJECT-TYPE
			SYNTAX	INTEGER
			MAX-ACCESS	read-only
			STATUS	current
			::= { hmWanMbusF7 46 }

hmWanMbusF7Value14		OBJECT-TYPE
			SYNTAX	INTEGER
			MAX-ACCESS	read-only
			STATUS	current
			::= { hmWanMbusF7 47 }

hmWanMbusF7VIF15		OBJECT-TYPE
			SYNTAX	INTEGER
			MAX-ACCESS	read-only
			STATUS	current
			::= { hmWanMbusF7 48 }

hmWanMbusF7Value15		OBJECT-TYPE
			SYNTAX	INTEGER
			MAX-ACCESS	read-only
			STATUS	current
			::= { hmWanMbusF7 49 }

hmWanMbusF7VIF16		OBJECT-TYPE
			SYNTAX	INTEGER
			MAX-ACCESS	read-only
			STATUS	current
			::= { hmWanMbusF7 50 }

hmWanMbusF7Value16		OBJECT-TYPE
			SYNTAX	INTEGER
			MAX-ACCESS	read-only
			STATUS	current
			::= { hmWanMbusF7 51 }

hmWanMbusF7VIF17		OBJECT-TYPE
			SYNTAX	INTEGER
			MAX-ACCESS	read-only
			STATUS	current
			::= { hmWanMbusF7 52 }

hmWanMbusF7Value17		OBJECT-TYPE
			SYNTAX	INTEGER
			MAX-ACCESS	read-only
			STATUS	current
			::= { hmWanMbusF7 53 }

hmWanMbusF7VIF18		OBJECT-TYPE
			SYNTAX	INTEGER
			MAX-ACCESS	read-only
			STATUS	current
			::= { hmWanMbusF7 54 }

hmWanMbusF7Value18		OBJECT-TYPE
			SYNTAX	INTEGER
			MAX-ACCESS	read-only
			STATUS	current
			::= { hmWanMbusF7 55 }

hmWanMbusF7VIF19		OBJECT-TYPE
			SYNTAX	INTEGER
			MAX-ACCESS	read-only
			STATUS	current
			::= { hmWanMbusF7 56 }

hmWanMbusF7Value19		OBJECT-TYPE
			SYNTAX	INTEGER
			MAX-ACCESS	read-only
			STATUS	current
			::= { hmWanMbusF7 57 }

hmWanMbusF7VIF1A		OBJECT-TYPE
			SYNTAX	INTEGER
			MAX-ACCESS	read-only
			STATUS	current
			::= { hmWanMbusF7 58 }

hmWanMbusF7Value1A		OBJECT-TYPE
			SYNTAX	INTEGER
			MAX-ACCESS	read-only
			STATUS	current
			::= { hmWanMbusF7 59 }

hmWanMbusF7VIF1B		OBJECT-TYPE
			SYNTAX	INTEGER
			MAX-ACCESS	read-only
			STATUS	current
			::= { hmWanMbusF7 60 }

hmWanMbusF7Value1B		OBJECT-TYPE
			SYNTAX	INTEGER
			MAX-ACCESS	read-only
			STATUS	current
			::= { hmWanMbusF7 61 }

hmWanMbusF7VIF1C		OBJECT-TYPE
			SYNTAX	INTEGER
			MAX-ACCESS	read-only
			STATUS	current
			::= { hmWanMbusF7 62 }

hmWanMbusF7Value1C		OBJECT-TYPE
			SYNTAX	INTEGER
			MAX-ACCESS	read-only
			STATUS	current
			::= { hmWanMbusF7 63 }

hmWanMbusF7VIF1D		OBJECT-TYPE
			SYNTAX	INTEGER
			MAX-ACCESS	read-only
			STATUS	current
			::= { hmWanMbusF7 64 }

hmWanMbusF7Value1D		OBJECT-TYPE
			SYNTAX	INTEGER
			MAX-ACCESS	read-only
			STATUS	current
			::= { hmWanMbusF7 65 }

hmWanMbusF7VIF1E		OBJECT-TYPE
			SYNTAX	INTEGER
			MAX-ACCESS	read-only
			STATUS	current
			::= { hmWanMbusF7 66 }

hmWanMbusF7Value1E		OBJECT-TYPE
			SYNTAX	INTEGER
			MAX-ACCESS	read-only
			STATUS	current
			::= { hmWanMbusF7 67 }

hmWanMbusF7VIF1F		OBJECT-TYPE
			SYNTAX	INTEGER
			MAX-ACCESS	read-only
			STATUS	current
			::= { hmWanMbusF7 68 }

hmWanMbusF7Value1F		OBJECT-TYPE
			SYNTAX	INTEGER
			MAX-ACCESS	read-only
			STATUS	current
			::= { hmWanMbusF7 69 }

hmWanMbusF7VIF20		OBJECT-TYPE
			SYNTAX	INTEGER
			MAX-ACCESS	read-only
			STATUS	current
			::= { hmWanMbusF7 70 }

hmWanMbusF7Value20		OBJECT-TYPE
			SYNTAX	INTEGER
			MAX-ACCESS	read-only
			STATUS	current
			::= { hmWanMbusF7 71 }

hmWanMbusF7VIF21		OBJECT-TYPE
			SYNTAX	INTEGER
			MAX-ACCESS	read-only
			STATUS	current
			::= { hmWanMbusF7 72 }

hmWanMbusF7Value21		OBJECT-TYPE
			SYNTAX	INTEGER
			MAX-ACCESS	read-only
			STATUS	current
			::= { hmWanMbusF7 73 }

hmWanMbusF7VIF22		OBJECT-TYPE
			SYNTAX	INTEGER
			MAX-ACCESS	read-only
			STATUS	current
			::= { hmWanMbusF7 74 }

hmWanMbusF7Value22		OBJECT-TYPE
			SYNTAX	INTEGER
			MAX-ACCESS	read-only
			STATUS	current
			::= { hmWanMbusF7 75 }

hmWanMbusF7VIF23		OBJECT-TYPE
			SYNTAX	INTEGER
			MAX-ACCESS	read-only
			STATUS	current
			::= { hmWanMbusF7 76 }

hmWanMbusF7Value23		OBJECT-TYPE
			SYNTAX	INTEGER
			MAX-ACCESS	read-only
			STATUS	current
			::= { hmWanMbusF7 77 }

hmWanMbusF7VIF24		OBJECT-TYPE
			SYNTAX	INTEGER
			MAX-ACCESS	read-only
			STATUS	current
			::= { hmWanMbusF7 78 }

hmWanMbusF7Value24		OBJECT-TYPE
			SYNTAX	INTEGER
			MAX-ACCESS	read-only
			STATUS	current
			::= { hmWanMbusF7 79 }

hmWanMbusF7VIF25		OBJECT-TYPE
			SYNTAX	INTEGER
			MAX-ACCESS	read-only
			STATUS	current
			::= { hmWanMbusF7 80 }

hmWanMbusF7Value25		OBJECT-TYPE
			SYNTAX	INTEGER
			MAX-ACCESS	read-only
			STATUS	current
			::= { hmWanMbusF7 81 }

hmWanMbusF7VIF26		OBJECT-TYPE
			SYNTAX	INTEGER
			MAX-ACCESS	read-only
			STATUS	current
			::= { hmWanMbusF7 82 }

hmWanMbusF7Value26		OBJECT-TYPE
			SYNTAX	INTEGER
			MAX-ACCESS	read-only
			STATUS	current
			::= { hmWanMbusF7 83 }

hmWanMbusF7VIF27		OBJECT-TYPE
			SYNTAX	INTEGER
			MAX-ACCESS	read-only
			STATUS	current
			::= { hmWanMbusF7 84 }

hmWanMbusF7Value27		OBJECT-TYPE
			SYNTAX	INTEGER
			MAX-ACCESS	read-only
			STATUS	current
			::= { hmWanMbusF7 85 }

hmWanMbusF7VIF28		OBJECT-TYPE
			SYNTAX	INTEGER
			MAX-ACCESS	read-only
			STATUS	current
			::= { hmWanMbusF7 86 }

hmWanMbusF7Value28		OBJECT-TYPE
			SYNTAX	INTEGER
			MAX-ACCESS	read-only
			STATUS	current
			::= { hmWanMbusF7 87 }

hmWanMbusF7VIF29		OBJECT-TYPE
			SYNTAX	INTEGER
			MAX-ACCESS	read-only
			STATUS	current
			::= { hmWanMbusF7 88 }

hmWanMbusF7Value29		OBJECT-TYPE
			SYNTAX	INTEGER
			MAX-ACCESS	read-only
			STATUS	current
			::= { hmWanMbusF7 89 }

hmWanMbusF7VIF2A		OBJECT-TYPE
			SYNTAX	INTEGER
			MAX-ACCESS	read-only
			STATUS	current
			::= { hmWanMbusF7 90 }

hmWanMbusF7Value2A		OBJECT-TYPE
			SYNTAX	INTEGER
			MAX-ACCESS	read-only
			STATUS	current
			::= { hmWanMbusF7 91 }

hmWanMbusF7VIF2B		OBJECT-TYPE
			SYNTAX	INTEGER
			MAX-ACCESS	read-only
			STATUS	current
			::= { hmWanMbusF7 92 }

hmWanMbusF7Value2B		OBJECT-TYPE
			SYNTAX	INTEGER
			MAX-ACCESS	read-only
			STATUS	current
			::= { hmWanMbusF7 93 }

hmWanMbusF7VIF2C		OBJECT-TYPE
			SYNTAX	INTEGER
			MAX-ACCESS	read-only
			STATUS	current
			::= { hmWanMbusF7 94 }

hmWanMbusF7Value2C		OBJECT-TYPE
			SYNTAX	INTEGER
			MAX-ACCESS	read-only
			STATUS	current
			::= { hmWanMbusF7 95 }

hmWanMbusF7VIF2D		OBJECT-TYPE
			SYNTAX	INTEGER
			MAX-ACCESS	read-only
			STATUS	current
			::= { hmWanMbusF7 96 }

hmWanMbusF7Value2D		OBJECT-TYPE
			SYNTAX	INTEGER
			MAX-ACCESS	read-only
			STATUS	current
			::= { hmWanMbusF7 97 }

hmWanMbusF7VIF2E		OBJECT-TYPE
			SYNTAX	INTEGER
			MAX-ACCESS	read-only
			STATUS	current
			::= { hmWanMbusF7 98 }

hmWanMbusF7Value2E		OBJECT-TYPE
			SYNTAX	INTEGER
			MAX-ACCESS	read-only
			STATUS	current
			::= { hmWanMbusF7 99 }

hmWanMbusF7VIF2F		OBJECT-TYPE
			SYNTAX	INTEGER
			MAX-ACCESS	read-only
			STATUS	current
			::= { hmWanMbusF7 100 }

hmWanMbusF7Value2F		OBJECT-TYPE
			SYNTAX	INTEGER
			MAX-ACCESS	read-only
			STATUS	current
			::= { hmWanMbusF7 101 }

hmWanMbusF8			OBJECT IDENTIFIER ::= { hmWanMbus 248 }

hmWanMbusF8IdNumber		OBJECT-TYPE
			SYNTAX	Gauge32
			MAX-ACCESS	read-only
			STATUS	current
			::= { hmWanMbusF8 1 }

hmWanMbusF8Manufacturer	OBJECT-TYPE
			SYNTAX	Gauge32
			MAX-ACCESS	read-only
			STATUS	current
			::= { hmWanMbusF8 2 }

hmWanMbusF8Version		OBJECT-TYPE
			SYNTAX	Gauge32
			MAX-ACCESS	read-only
			STATUS	current
			::= { hmWanMbusF8 3 }

hmWanMbusF8Medium		OBJECT-TYPE
			SYNTAX	Gauge32
			MAX-ACCESS	read-only
			STATUS	current
			::= { hmWanMbusF8 4 }

hmWanMbusF8Status		OBJECT-TYPE
			SYNTAX	Gauge32
			MAX-ACCESS	read-only
			STATUS	current
			::= { hmWanMbusF8 5 }

hmWanMbusF8VIF00		OBJECT-TYPE
			SYNTAX	INTEGER
			MAX-ACCESS	read-only
			STATUS	current
			::= { hmWanMbusF8 6 }

hmWanMbusF8Value00		OBJECT-TYPE
			SYNTAX	INTEGER
			MAX-ACCESS	read-only
			STATUS	current
			::= { hmWanMbusF8 7 }

hmWanMbusF8VIF01		OBJECT-TYPE
			SYNTAX	INTEGER
			MAX-ACCESS	read-only
			STATUS	current
			::= { hmWanMbusF8 8 }

hmWanMbusF8Value01		OBJECT-TYPE
			SYNTAX	INTEGER
			MAX-ACCESS	read-only
			STATUS	current
			::= { hmWanMbusF8 9 }

hmWanMbusF8VIF02		OBJECT-TYPE
			SYNTAX	INTEGER
			MAX-ACCESS	read-only
			STATUS	current
			::= { hmWanMbusF8 10 }

hmWanMbusF8Value02		OBJECT-TYPE
			SYNTAX	INTEGER
			MAX-ACCESS	read-only
			STATUS	current
			::= { hmWanMbusF8 11 }

hmWanMbusF8VIF03		OBJECT-TYPE
			SYNTAX	INTEGER
			MAX-ACCESS	read-only
			STATUS	current
			::= { hmWanMbusF8 12 }

hmWanMbusF8Value03		OBJECT-TYPE
			SYNTAX	INTEGER
			MAX-ACCESS	read-only
			STATUS	current
			::= { hmWanMbusF8 13 }

hmWanMbusF8VIF04		OBJECT-TYPE
			SYNTAX	INTEGER
			MAX-ACCESS	read-only
			STATUS	current
			::= { hmWanMbusF8 14 }

hmWanMbusF8Value04		OBJECT-TYPE
			SYNTAX	INTEGER
			MAX-ACCESS	read-only
			STATUS	current
			::= { hmWanMbusF8 15 }

hmWanMbusF8VIF05		OBJECT-TYPE
			SYNTAX	INTEGER
			MAX-ACCESS	read-only
			STATUS	current
			::= { hmWanMbusF8 16 }

hmWanMbusF8Value05		OBJECT-TYPE
			SYNTAX	INTEGER
			MAX-ACCESS	read-only
			STATUS	current
			::= { hmWanMbusF8 17 }

hmWanMbusF8VIF06		OBJECT-TYPE
			SYNTAX	INTEGER
			MAX-ACCESS	read-only
			STATUS	current
			::= { hmWanMbusF8 18 }

hmWanMbusF8Value06		OBJECT-TYPE
			SYNTAX	INTEGER
			MAX-ACCESS	read-only
			STATUS	current
			::= { hmWanMbusF8 19 }

hmWanMbusF8VIF07		OBJECT-TYPE
			SYNTAX	INTEGER
			MAX-ACCESS	read-only
			STATUS	current
			::= { hmWanMbusF8 20 }

hmWanMbusF8Value07		OBJECT-TYPE
			SYNTAX	INTEGER
			MAX-ACCESS	read-only
			STATUS	current
			::= { hmWanMbusF8 21 }

hmWanMbusF8VIF08		OBJECT-TYPE
			SYNTAX	INTEGER
			MAX-ACCESS	read-only
			STATUS	current
			::= { hmWanMbusF8 22 }

hmWanMbusF8Value08		OBJECT-TYPE
			SYNTAX	INTEGER
			MAX-ACCESS	read-only
			STATUS	current
			::= { hmWanMbusF8 23 }

hmWanMbusF8VIF09		OBJECT-TYPE
			SYNTAX	INTEGER
			MAX-ACCESS	read-only
			STATUS	current
			::= { hmWanMbusF8 24 }

hmWanMbusF8Value09		OBJECT-TYPE
			SYNTAX	INTEGER
			MAX-ACCESS	read-only
			STATUS	current
			::= { hmWanMbusF8 25 }

hmWanMbusF8VIF0A		OBJECT-TYPE
			SYNTAX	INTEGER
			MAX-ACCESS	read-only
			STATUS	current
			::= { hmWanMbusF8 26 }

hmWanMbusF8Value0A		OBJECT-TYPE
			SYNTAX	INTEGER
			MAX-ACCESS	read-only
			STATUS	current
			::= { hmWanMbusF8 27 }

hmWanMbusF8VIF0B		OBJECT-TYPE
			SYNTAX	INTEGER
			MAX-ACCESS	read-only
			STATUS	current
			::= { hmWanMbusF8 28 }

hmWanMbusF8Value0B		OBJECT-TYPE
			SYNTAX	INTEGER
			MAX-ACCESS	read-only
			STATUS	current
			::= { hmWanMbusF8 29 }

hmWanMbusF8VIF0C		OBJECT-TYPE
			SYNTAX	INTEGER
			MAX-ACCESS	read-only
			STATUS	current
			::= { hmWanMbusF8 30 }

hmWanMbusF8Value0C		OBJECT-TYPE
			SYNTAX	INTEGER
			MAX-ACCESS	read-only
			STATUS	current
			::= { hmWanMbusF8 31 }

hmWanMbusF8VIF0D		OBJECT-TYPE
			SYNTAX	INTEGER
			MAX-ACCESS	read-only
			STATUS	current
			::= { hmWanMbusF8 32 }

hmWanMbusF8Value0D		OBJECT-TYPE
			SYNTAX	INTEGER
			MAX-ACCESS	read-only
			STATUS	current
			::= { hmWanMbusF8 33 }

hmWanMbusF8VIF0E		OBJECT-TYPE
			SYNTAX	INTEGER
			MAX-ACCESS	read-only
			STATUS	current
			::= { hmWanMbusF8 34 }

hmWanMbusF8Value0E		OBJECT-TYPE
			SYNTAX	INTEGER
			MAX-ACCESS	read-only
			STATUS	current
			::= { hmWanMbusF8 35 }

hmWanMbusF8VIF0F		OBJECT-TYPE
			SYNTAX	INTEGER
			MAX-ACCESS	read-only
			STATUS	current
			::= { hmWanMbusF8 36 }

hmWanMbusF8Value0F		OBJECT-TYPE
			SYNTAX	INTEGER
			MAX-ACCESS	read-only
			STATUS	current
			::= { hmWanMbusF8 37 }

hmWanMbusF8VIF10		OBJECT-TYPE
			SYNTAX	INTEGER
			MAX-ACCESS	read-only
			STATUS	current
			::= { hmWanMbusF8 38 }

hmWanMbusF8Value10		OBJECT-TYPE
			SYNTAX	INTEGER
			MAX-ACCESS	read-only
			STATUS	current
			::= { hmWanMbusF8 39 }

hmWanMbusF8VIF11		OBJECT-TYPE
			SYNTAX	INTEGER
			MAX-ACCESS	read-only
			STATUS	current
			::= { hmWanMbusF8 40 }

hmWanMbusF8Value11		OBJECT-TYPE
			SYNTAX	INTEGER
			MAX-ACCESS	read-only
			STATUS	current
			::= { hmWanMbusF8 41 }

hmWanMbusF8VIF12		OBJECT-TYPE
			SYNTAX	INTEGER
			MAX-ACCESS	read-only
			STATUS	current
			::= { hmWanMbusF8 42 }

hmWanMbusF8Value12		OBJECT-TYPE
			SYNTAX	INTEGER
			MAX-ACCESS	read-only
			STATUS	current
			::= { hmWanMbusF8 43 }

hmWanMbusF8VIF13		OBJECT-TYPE
			SYNTAX	INTEGER
			MAX-ACCESS	read-only
			STATUS	current
			::= { hmWanMbusF8 44 }

hmWanMbusF8Value13		OBJECT-TYPE
			SYNTAX	INTEGER
			MAX-ACCESS	read-only
			STATUS	current
			::= { hmWanMbusF8 45 }

hmWanMbusF8VIF14		OBJECT-TYPE
			SYNTAX	INTEGER
			MAX-ACCESS	read-only
			STATUS	current
			::= { hmWanMbusF8 46 }

hmWanMbusF8Value14		OBJECT-TYPE
			SYNTAX	INTEGER
			MAX-ACCESS	read-only
			STATUS	current
			::= { hmWanMbusF8 47 }

hmWanMbusF8VIF15		OBJECT-TYPE
			SYNTAX	INTEGER
			MAX-ACCESS	read-only
			STATUS	current
			::= { hmWanMbusF8 48 }

hmWanMbusF8Value15		OBJECT-TYPE
			SYNTAX	INTEGER
			MAX-ACCESS	read-only
			STATUS	current
			::= { hmWanMbusF8 49 }

hmWanMbusF8VIF16		OBJECT-TYPE
			SYNTAX	INTEGER
			MAX-ACCESS	read-only
			STATUS	current
			::= { hmWanMbusF8 50 }

hmWanMbusF8Value16		OBJECT-TYPE
			SYNTAX	INTEGER
			MAX-ACCESS	read-only
			STATUS	current
			::= { hmWanMbusF8 51 }

hmWanMbusF8VIF17		OBJECT-TYPE
			SYNTAX	INTEGER
			MAX-ACCESS	read-only
			STATUS	current
			::= { hmWanMbusF8 52 }

hmWanMbusF8Value17		OBJECT-TYPE
			SYNTAX	INTEGER
			MAX-ACCESS	read-only
			STATUS	current
			::= { hmWanMbusF8 53 }

hmWanMbusF8VIF18		OBJECT-TYPE
			SYNTAX	INTEGER
			MAX-ACCESS	read-only
			STATUS	current
			::= { hmWanMbusF8 54 }

hmWanMbusF8Value18		OBJECT-TYPE
			SYNTAX	INTEGER
			MAX-ACCESS	read-only
			STATUS	current
			::= { hmWanMbusF8 55 }

hmWanMbusF8VIF19		OBJECT-TYPE
			SYNTAX	INTEGER
			MAX-ACCESS	read-only
			STATUS	current
			::= { hmWanMbusF8 56 }

hmWanMbusF8Value19		OBJECT-TYPE
			SYNTAX	INTEGER
			MAX-ACCESS	read-only
			STATUS	current
			::= { hmWanMbusF8 57 }

hmWanMbusF8VIF1A		OBJECT-TYPE
			SYNTAX	INTEGER
			MAX-ACCESS	read-only
			STATUS	current
			::= { hmWanMbusF8 58 }

hmWanMbusF8Value1A		OBJECT-TYPE
			SYNTAX	INTEGER
			MAX-ACCESS	read-only
			STATUS	current
			::= { hmWanMbusF8 59 }

hmWanMbusF8VIF1B		OBJECT-TYPE
			SYNTAX	INTEGER
			MAX-ACCESS	read-only
			STATUS	current
			::= { hmWanMbusF8 60 }

hmWanMbusF8Value1B		OBJECT-TYPE
			SYNTAX	INTEGER
			MAX-ACCESS	read-only
			STATUS	current
			::= { hmWanMbusF8 61 }

hmWanMbusF8VIF1C		OBJECT-TYPE
			SYNTAX	INTEGER
			MAX-ACCESS	read-only
			STATUS	current
			::= { hmWanMbusF8 62 }

hmWanMbusF8Value1C		OBJECT-TYPE
			SYNTAX	INTEGER
			MAX-ACCESS	read-only
			STATUS	current
			::= { hmWanMbusF8 63 }

hmWanMbusF8VIF1D		OBJECT-TYPE
			SYNTAX	INTEGER
			MAX-ACCESS	read-only
			STATUS	current
			::= { hmWanMbusF8 64 }

hmWanMbusF8Value1D		OBJECT-TYPE
			SYNTAX	INTEGER
			MAX-ACCESS	read-only
			STATUS	current
			::= { hmWanMbusF8 65 }

hmWanMbusF8VIF1E		OBJECT-TYPE
			SYNTAX	INTEGER
			MAX-ACCESS	read-only
			STATUS	current
			::= { hmWanMbusF8 66 }

hmWanMbusF8Value1E		OBJECT-TYPE
			SYNTAX	INTEGER
			MAX-ACCESS	read-only
			STATUS	current
			::= { hmWanMbusF8 67 }

hmWanMbusF8VIF1F		OBJECT-TYPE
			SYNTAX	INTEGER
			MAX-ACCESS	read-only
			STATUS	current
			::= { hmWanMbusF8 68 }

hmWanMbusF8Value1F		OBJECT-TYPE
			SYNTAX	INTEGER
			MAX-ACCESS	read-only
			STATUS	current
			::= { hmWanMbusF8 69 }

hmWanMbusF8VIF20		OBJECT-TYPE
			SYNTAX	INTEGER
			MAX-ACCESS	read-only
			STATUS	current
			::= { hmWanMbusF8 70 }

hmWanMbusF8Value20		OBJECT-TYPE
			SYNTAX	INTEGER
			MAX-ACCESS	read-only
			STATUS	current
			::= { hmWanMbusF8 71 }

hmWanMbusF8VIF21		OBJECT-TYPE
			SYNTAX	INTEGER
			MAX-ACCESS	read-only
			STATUS	current
			::= { hmWanMbusF8 72 }

hmWanMbusF8Value21		OBJECT-TYPE
			SYNTAX	INTEGER
			MAX-ACCESS	read-only
			STATUS	current
			::= { hmWanMbusF8 73 }

hmWanMbusF8VIF22		OBJECT-TYPE
			SYNTAX	INTEGER
			MAX-ACCESS	read-only
			STATUS	current
			::= { hmWanMbusF8 74 }

hmWanMbusF8Value22		OBJECT-TYPE
			SYNTAX	INTEGER
			MAX-ACCESS	read-only
			STATUS	current
			::= { hmWanMbusF8 75 }

hmWanMbusF8VIF23		OBJECT-TYPE
			SYNTAX	INTEGER
			MAX-ACCESS	read-only
			STATUS	current
			::= { hmWanMbusF8 76 }

hmWanMbusF8Value23		OBJECT-TYPE
			SYNTAX	INTEGER
			MAX-ACCESS	read-only
			STATUS	current
			::= { hmWanMbusF8 77 }

hmWanMbusF8VIF24		OBJECT-TYPE
			SYNTAX	INTEGER
			MAX-ACCESS	read-only
			STATUS	current
			::= { hmWanMbusF8 78 }

hmWanMbusF8Value24		OBJECT-TYPE
			SYNTAX	INTEGER
			MAX-ACCESS	read-only
			STATUS	current
			::= { hmWanMbusF8 79 }

hmWanMbusF8VIF25		OBJECT-TYPE
			SYNTAX	INTEGER
			MAX-ACCESS	read-only
			STATUS	current
			::= { hmWanMbusF8 80 }

hmWanMbusF8Value25		OBJECT-TYPE
			SYNTAX	INTEGER
			MAX-ACCESS	read-only
			STATUS	current
			::= { hmWanMbusF8 81 }

hmWanMbusF8VIF26		OBJECT-TYPE
			SYNTAX	INTEGER
			MAX-ACCESS	read-only
			STATUS	current
			::= { hmWanMbusF8 82 }

hmWanMbusF8Value26		OBJECT-TYPE
			SYNTAX	INTEGER
			MAX-ACCESS	read-only
			STATUS	current
			::= { hmWanMbusF8 83 }

hmWanMbusF8VIF27		OBJECT-TYPE
			SYNTAX	INTEGER
			MAX-ACCESS	read-only
			STATUS	current
			::= { hmWanMbusF8 84 }

hmWanMbusF8Value27		OBJECT-TYPE
			SYNTAX	INTEGER
			MAX-ACCESS	read-only
			STATUS	current
			::= { hmWanMbusF8 85 }

hmWanMbusF8VIF28		OBJECT-TYPE
			SYNTAX	INTEGER
			MAX-ACCESS	read-only
			STATUS	current
			::= { hmWanMbusF8 86 }

hmWanMbusF8Value28		OBJECT-TYPE
			SYNTAX	INTEGER
			MAX-ACCESS	read-only
			STATUS	current
			::= { hmWanMbusF8 87 }

hmWanMbusF8VIF29		OBJECT-TYPE
			SYNTAX	INTEGER
			MAX-ACCESS	read-only
			STATUS	current
			::= { hmWanMbusF8 88 }

hmWanMbusF8Value29		OBJECT-TYPE
			SYNTAX	INTEGER
			MAX-ACCESS	read-only
			STATUS	current
			::= { hmWanMbusF8 89 }

hmWanMbusF8VIF2A		OBJECT-TYPE
			SYNTAX	INTEGER
			MAX-ACCESS	read-only
			STATUS	current
			::= { hmWanMbusF8 90 }

hmWanMbusF8Value2A		OBJECT-TYPE
			SYNTAX	INTEGER
			MAX-ACCESS	read-only
			STATUS	current
			::= { hmWanMbusF8 91 }

hmWanMbusF8VIF2B		OBJECT-TYPE
			SYNTAX	INTEGER
			MAX-ACCESS	read-only
			STATUS	current
			::= { hmWanMbusF8 92 }

hmWanMbusF8Value2B		OBJECT-TYPE
			SYNTAX	INTEGER
			MAX-ACCESS	read-only
			STATUS	current
			::= { hmWanMbusF8 93 }

hmWanMbusF8VIF2C		OBJECT-TYPE
			SYNTAX	INTEGER
			MAX-ACCESS	read-only
			STATUS	current
			::= { hmWanMbusF8 94 }

hmWanMbusF8Value2C		OBJECT-TYPE
			SYNTAX	INTEGER
			MAX-ACCESS	read-only
			STATUS	current
			::= { hmWanMbusF8 95 }

hmWanMbusF8VIF2D		OBJECT-TYPE
			SYNTAX	INTEGER
			MAX-ACCESS	read-only
			STATUS	current
			::= { hmWanMbusF8 96 }

hmWanMbusF8Value2D		OBJECT-TYPE
			SYNTAX	INTEGER
			MAX-ACCESS	read-only
			STATUS	current
			::= { hmWanMbusF8 97 }

hmWanMbusF8VIF2E		OBJECT-TYPE
			SYNTAX	INTEGER
			MAX-ACCESS	read-only
			STATUS	current
			::= { hmWanMbusF8 98 }

hmWanMbusF8Value2E		OBJECT-TYPE
			SYNTAX	INTEGER
			MAX-ACCESS	read-only
			STATUS	current
			::= { hmWanMbusF8 99 }

hmWanMbusF8VIF2F		OBJECT-TYPE
			SYNTAX	INTEGER
			MAX-ACCESS	read-only
			STATUS	current
			::= { hmWanMbusF8 100 }

hmWanMbusF8Value2F		OBJECT-TYPE
			SYNTAX	INTEGER
			MAX-ACCESS	read-only
			STATUS	current
			::= { hmWanMbusF8 101 }

hmWanMbusF9			OBJECT IDENTIFIER ::= { hmWanMbus 249 }

hmWanMbusF9IdNumber		OBJECT-TYPE
			SYNTAX	Gauge32
			MAX-ACCESS	read-only
			STATUS	current
			::= { hmWanMbusF9 1 }

hmWanMbusF9Manufacturer	OBJECT-TYPE
			SYNTAX	Gauge32
			MAX-ACCESS	read-only
			STATUS	current
			::= { hmWanMbusF9 2 }

hmWanMbusF9Version		OBJECT-TYPE
			SYNTAX	Gauge32
			MAX-ACCESS	read-only
			STATUS	current
			::= { hmWanMbusF9 3 }

hmWanMbusF9Medium		OBJECT-TYPE
			SYNTAX	Gauge32
			MAX-ACCESS	read-only
			STATUS	current
			::= { hmWanMbusF9 4 }

hmWanMbusF9Status		OBJECT-TYPE
			SYNTAX	Gauge32
			MAX-ACCESS	read-only
			STATUS	current
			::= { hmWanMbusF9 5 }

hmWanMbusF9VIF00		OBJECT-TYPE
			SYNTAX	INTEGER
			MAX-ACCESS	read-only
			STATUS	current
			::= { hmWanMbusF9 6 }

hmWanMbusF9Value00		OBJECT-TYPE
			SYNTAX	INTEGER
			MAX-ACCESS	read-only
			STATUS	current
			::= { hmWanMbusF9 7 }

hmWanMbusF9VIF01		OBJECT-TYPE
			SYNTAX	INTEGER
			MAX-ACCESS	read-only
			STATUS	current
			::= { hmWanMbusF9 8 }

hmWanMbusF9Value01		OBJECT-TYPE
			SYNTAX	INTEGER
			MAX-ACCESS	read-only
			STATUS	current
			::= { hmWanMbusF9 9 }

hmWanMbusF9VIF02		OBJECT-TYPE
			SYNTAX	INTEGER
			MAX-ACCESS	read-only
			STATUS	current
			::= { hmWanMbusF9 10 }

hmWanMbusF9Value02		OBJECT-TYPE
			SYNTAX	INTEGER
			MAX-ACCESS	read-only
			STATUS	current
			::= { hmWanMbusF9 11 }

hmWanMbusF9VIF03		OBJECT-TYPE
			SYNTAX	INTEGER
			MAX-ACCESS	read-only
			STATUS	current
			::= { hmWanMbusF9 12 }

hmWanMbusF9Value03		OBJECT-TYPE
			SYNTAX	INTEGER
			MAX-ACCESS	read-only
			STATUS	current
			::= { hmWanMbusF9 13 }

hmWanMbusF9VIF04		OBJECT-TYPE
			SYNTAX	INTEGER
			MAX-ACCESS	read-only
			STATUS	current
			::= { hmWanMbusF9 14 }

hmWanMbusF9Value04		OBJECT-TYPE
			SYNTAX	INTEGER
			MAX-ACCESS	read-only
			STATUS	current
			::= { hmWanMbusF9 15 }

hmWanMbusF9VIF05		OBJECT-TYPE
			SYNTAX	INTEGER
			MAX-ACCESS	read-only
			STATUS	current
			::= { hmWanMbusF9 16 }

hmWanMbusF9Value05		OBJECT-TYPE
			SYNTAX	INTEGER
			MAX-ACCESS	read-only
			STATUS	current
			::= { hmWanMbusF9 17 }

hmWanMbusF9VIF06		OBJECT-TYPE
			SYNTAX	INTEGER
			MAX-ACCESS	read-only
			STATUS	current
			::= { hmWanMbusF9 18 }

hmWanMbusF9Value06		OBJECT-TYPE
			SYNTAX	INTEGER
			MAX-ACCESS	read-only
			STATUS	current
			::= { hmWanMbusF9 19 }

hmWanMbusF9VIF07		OBJECT-TYPE
			SYNTAX	INTEGER
			MAX-ACCESS	read-only
			STATUS	current
			::= { hmWanMbusF9 20 }

hmWanMbusF9Value07		OBJECT-TYPE
			SYNTAX	INTEGER
			MAX-ACCESS	read-only
			STATUS	current
			::= { hmWanMbusF9 21 }

hmWanMbusF9VIF08		OBJECT-TYPE
			SYNTAX	INTEGER
			MAX-ACCESS	read-only
			STATUS	current
			::= { hmWanMbusF9 22 }

hmWanMbusF9Value08		OBJECT-TYPE
			SYNTAX	INTEGER
			MAX-ACCESS	read-only
			STATUS	current
			::= { hmWanMbusF9 23 }

hmWanMbusF9VIF09		OBJECT-TYPE
			SYNTAX	INTEGER
			MAX-ACCESS	read-only
			STATUS	current
			::= { hmWanMbusF9 24 }

hmWanMbusF9Value09		OBJECT-TYPE
			SYNTAX	INTEGER
			MAX-ACCESS	read-only
			STATUS	current
			::= { hmWanMbusF9 25 }

hmWanMbusF9VIF0A		OBJECT-TYPE
			SYNTAX	INTEGER
			MAX-ACCESS	read-only
			STATUS	current
			::= { hmWanMbusF9 26 }

hmWanMbusF9Value0A		OBJECT-TYPE
			SYNTAX	INTEGER
			MAX-ACCESS	read-only
			STATUS	current
			::= { hmWanMbusF9 27 }

hmWanMbusF9VIF0B		OBJECT-TYPE
			SYNTAX	INTEGER
			MAX-ACCESS	read-only
			STATUS	current
			::= { hmWanMbusF9 28 }

hmWanMbusF9Value0B		OBJECT-TYPE
			SYNTAX	INTEGER
			MAX-ACCESS	read-only
			STATUS	current
			::= { hmWanMbusF9 29 }

hmWanMbusF9VIF0C		OBJECT-TYPE
			SYNTAX	INTEGER
			MAX-ACCESS	read-only
			STATUS	current
			::= { hmWanMbusF9 30 }

hmWanMbusF9Value0C		OBJECT-TYPE
			SYNTAX	INTEGER
			MAX-ACCESS	read-only
			STATUS	current
			::= { hmWanMbusF9 31 }

hmWanMbusF9VIF0D		OBJECT-TYPE
			SYNTAX	INTEGER
			MAX-ACCESS	read-only
			STATUS	current
			::= { hmWanMbusF9 32 }

hmWanMbusF9Value0D		OBJECT-TYPE
			SYNTAX	INTEGER
			MAX-ACCESS	read-only
			STATUS	current
			::= { hmWanMbusF9 33 }

hmWanMbusF9VIF0E		OBJECT-TYPE
			SYNTAX	INTEGER
			MAX-ACCESS	read-only
			STATUS	current
			::= { hmWanMbusF9 34 }

hmWanMbusF9Value0E		OBJECT-TYPE
			SYNTAX	INTEGER
			MAX-ACCESS	read-only
			STATUS	current
			::= { hmWanMbusF9 35 }

hmWanMbusF9VIF0F		OBJECT-TYPE
			SYNTAX	INTEGER
			MAX-ACCESS	read-only
			STATUS	current
			::= { hmWanMbusF9 36 }

hmWanMbusF9Value0F		OBJECT-TYPE
			SYNTAX	INTEGER
			MAX-ACCESS	read-only
			STATUS	current
			::= { hmWanMbusF9 37 }

hmWanMbusF9VIF10		OBJECT-TYPE
			SYNTAX	INTEGER
			MAX-ACCESS	read-only
			STATUS	current
			::= { hmWanMbusF9 38 }

hmWanMbusF9Value10		OBJECT-TYPE
			SYNTAX	INTEGER
			MAX-ACCESS	read-only
			STATUS	current
			::= { hmWanMbusF9 39 }

hmWanMbusF9VIF11		OBJECT-TYPE
			SYNTAX	INTEGER
			MAX-ACCESS	read-only
			STATUS	current
			::= { hmWanMbusF9 40 }

hmWanMbusF9Value11		OBJECT-TYPE
			SYNTAX	INTEGER
			MAX-ACCESS	read-only
			STATUS	current
			::= { hmWanMbusF9 41 }

hmWanMbusF9VIF12		OBJECT-TYPE
			SYNTAX	INTEGER
			MAX-ACCESS	read-only
			STATUS	current
			::= { hmWanMbusF9 42 }

hmWanMbusF9Value12		OBJECT-TYPE
			SYNTAX	INTEGER
			MAX-ACCESS	read-only
			STATUS	current
			::= { hmWanMbusF9 43 }

hmWanMbusF9VIF13		OBJECT-TYPE
			SYNTAX	INTEGER
			MAX-ACCESS	read-only
			STATUS	current
			::= { hmWanMbusF9 44 }

hmWanMbusF9Value13		OBJECT-TYPE
			SYNTAX	INTEGER
			MAX-ACCESS	read-only
			STATUS	current
			::= { hmWanMbusF9 45 }

hmWanMbusF9VIF14		OBJECT-TYPE
			SYNTAX	INTEGER
			MAX-ACCESS	read-only
			STATUS	current
			::= { hmWanMbusF9 46 }

hmWanMbusF9Value14		OBJECT-TYPE
			SYNTAX	INTEGER
			MAX-ACCESS	read-only
			STATUS	current
			::= { hmWanMbusF9 47 }

hmWanMbusF9VIF15		OBJECT-TYPE
			SYNTAX	INTEGER
			MAX-ACCESS	read-only
			STATUS	current
			::= { hmWanMbusF9 48 }

hmWanMbusF9Value15		OBJECT-TYPE
			SYNTAX	INTEGER
			MAX-ACCESS	read-only
			STATUS	current
			::= { hmWanMbusF9 49 }

hmWanMbusF9VIF16		OBJECT-TYPE
			SYNTAX	INTEGER
			MAX-ACCESS	read-only
			STATUS	current
			::= { hmWanMbusF9 50 }

hmWanMbusF9Value16		OBJECT-TYPE
			SYNTAX	INTEGER
			MAX-ACCESS	read-only
			STATUS	current
			::= { hmWanMbusF9 51 }

hmWanMbusF9VIF17		OBJECT-TYPE
			SYNTAX	INTEGER
			MAX-ACCESS	read-only
			STATUS	current
			::= { hmWanMbusF9 52 }

hmWanMbusF9Value17		OBJECT-TYPE
			SYNTAX	INTEGER
			MAX-ACCESS	read-only
			STATUS	current
			::= { hmWanMbusF9 53 }

hmWanMbusF9VIF18		OBJECT-TYPE
			SYNTAX	INTEGER
			MAX-ACCESS	read-only
			STATUS	current
			::= { hmWanMbusF9 54 }

hmWanMbusF9Value18		OBJECT-TYPE
			SYNTAX	INTEGER
			MAX-ACCESS	read-only
			STATUS	current
			::= { hmWanMbusF9 55 }

hmWanMbusF9VIF19		OBJECT-TYPE
			SYNTAX	INTEGER
			MAX-ACCESS	read-only
			STATUS	current
			::= { hmWanMbusF9 56 }

hmWanMbusF9Value19		OBJECT-TYPE
			SYNTAX	INTEGER
			MAX-ACCESS	read-only
			STATUS	current
			::= { hmWanMbusF9 57 }

hmWanMbusF9VIF1A		OBJECT-TYPE
			SYNTAX	INTEGER
			MAX-ACCESS	read-only
			STATUS	current
			::= { hmWanMbusF9 58 }

hmWanMbusF9Value1A		OBJECT-TYPE
			SYNTAX	INTEGER
			MAX-ACCESS	read-only
			STATUS	current
			::= { hmWanMbusF9 59 }

hmWanMbusF9VIF1B		OBJECT-TYPE
			SYNTAX	INTEGER
			MAX-ACCESS	read-only
			STATUS	current
			::= { hmWanMbusF9 60 }

hmWanMbusF9Value1B		OBJECT-TYPE
			SYNTAX	INTEGER
			MAX-ACCESS	read-only
			STATUS	current
			::= { hmWanMbusF9 61 }

hmWanMbusF9VIF1C		OBJECT-TYPE
			SYNTAX	INTEGER
			MAX-ACCESS	read-only
			STATUS	current
			::= { hmWanMbusF9 62 }

hmWanMbusF9Value1C		OBJECT-TYPE
			SYNTAX	INTEGER
			MAX-ACCESS	read-only
			STATUS	current
			::= { hmWanMbusF9 63 }

hmWanMbusF9VIF1D		OBJECT-TYPE
			SYNTAX	INTEGER
			MAX-ACCESS	read-only
			STATUS	current
			::= { hmWanMbusF9 64 }

hmWanMbusF9Value1D		OBJECT-TYPE
			SYNTAX	INTEGER
			MAX-ACCESS	read-only
			STATUS	current
			::= { hmWanMbusF9 65 }

hmWanMbusF9VIF1E		OBJECT-TYPE
			SYNTAX	INTEGER
			MAX-ACCESS	read-only
			STATUS	current
			::= { hmWanMbusF9 66 }

hmWanMbusF9Value1E		OBJECT-TYPE
			SYNTAX	INTEGER
			MAX-ACCESS	read-only
			STATUS	current
			::= { hmWanMbusF9 67 }

hmWanMbusF9VIF1F		OBJECT-TYPE
			SYNTAX	INTEGER
			MAX-ACCESS	read-only
			STATUS	current
			::= { hmWanMbusF9 68 }

hmWanMbusF9Value1F		OBJECT-TYPE
			SYNTAX	INTEGER
			MAX-ACCESS	read-only
			STATUS	current
			::= { hmWanMbusF9 69 }

hmWanMbusF9VIF20		OBJECT-TYPE
			SYNTAX	INTEGER
			MAX-ACCESS	read-only
			STATUS	current
			::= { hmWanMbusF9 70 }

hmWanMbusF9Value20		OBJECT-TYPE
			SYNTAX	INTEGER
			MAX-ACCESS	read-only
			STATUS	current
			::= { hmWanMbusF9 71 }

hmWanMbusF9VIF21		OBJECT-TYPE
			SYNTAX	INTEGER
			MAX-ACCESS	read-only
			STATUS	current
			::= { hmWanMbusF9 72 }

hmWanMbusF9Value21		OBJECT-TYPE
			SYNTAX	INTEGER
			MAX-ACCESS	read-only
			STATUS	current
			::= { hmWanMbusF9 73 }

hmWanMbusF9VIF22		OBJECT-TYPE
			SYNTAX	INTEGER
			MAX-ACCESS	read-only
			STATUS	current
			::= { hmWanMbusF9 74 }

hmWanMbusF9Value22		OBJECT-TYPE
			SYNTAX	INTEGER
			MAX-ACCESS	read-only
			STATUS	current
			::= { hmWanMbusF9 75 }

hmWanMbusF9VIF23		OBJECT-TYPE
			SYNTAX	INTEGER
			MAX-ACCESS	read-only
			STATUS	current
			::= { hmWanMbusF9 76 }

hmWanMbusF9Value23		OBJECT-TYPE
			SYNTAX	INTEGER
			MAX-ACCESS	read-only
			STATUS	current
			::= { hmWanMbusF9 77 }

hmWanMbusF9VIF24		OBJECT-TYPE
			SYNTAX	INTEGER
			MAX-ACCESS	read-only
			STATUS	current
			::= { hmWanMbusF9 78 }

hmWanMbusF9Value24		OBJECT-TYPE
			SYNTAX	INTEGER
			MAX-ACCESS	read-only
			STATUS	current
			::= { hmWanMbusF9 79 }

hmWanMbusF9VIF25		OBJECT-TYPE
			SYNTAX	INTEGER
			MAX-ACCESS	read-only
			STATUS	current
			::= { hmWanMbusF9 80 }

hmWanMbusF9Value25		OBJECT-TYPE
			SYNTAX	INTEGER
			MAX-ACCESS	read-only
			STATUS	current
			::= { hmWanMbusF9 81 }

hmWanMbusF9VIF26		OBJECT-TYPE
			SYNTAX	INTEGER
			MAX-ACCESS	read-only
			STATUS	current
			::= { hmWanMbusF9 82 }

hmWanMbusF9Value26		OBJECT-TYPE
			SYNTAX	INTEGER
			MAX-ACCESS	read-only
			STATUS	current
			::= { hmWanMbusF9 83 }

hmWanMbusF9VIF27		OBJECT-TYPE
			SYNTAX	INTEGER
			MAX-ACCESS	read-only
			STATUS	current
			::= { hmWanMbusF9 84 }

hmWanMbusF9Value27		OBJECT-TYPE
			SYNTAX	INTEGER
			MAX-ACCESS	read-only
			STATUS	current
			::= { hmWanMbusF9 85 }

hmWanMbusF9VIF28		OBJECT-TYPE
			SYNTAX	INTEGER
			MAX-ACCESS	read-only
			STATUS	current
			::= { hmWanMbusF9 86 }

hmWanMbusF9Value28		OBJECT-TYPE
			SYNTAX	INTEGER
			MAX-ACCESS	read-only
			STATUS	current
			::= { hmWanMbusF9 87 }

hmWanMbusF9VIF29		OBJECT-TYPE
			SYNTAX	INTEGER
			MAX-ACCESS	read-only
			STATUS	current
			::= { hmWanMbusF9 88 }

hmWanMbusF9Value29		OBJECT-TYPE
			SYNTAX	INTEGER
			MAX-ACCESS	read-only
			STATUS	current
			::= { hmWanMbusF9 89 }

hmWanMbusF9VIF2A		OBJECT-TYPE
			SYNTAX	INTEGER
			MAX-ACCESS	read-only
			STATUS	current
			::= { hmWanMbusF9 90 }

hmWanMbusF9Value2A		OBJECT-TYPE
			SYNTAX	INTEGER
			MAX-ACCESS	read-only
			STATUS	current
			::= { hmWanMbusF9 91 }

hmWanMbusF9VIF2B		OBJECT-TYPE
			SYNTAX	INTEGER
			MAX-ACCESS	read-only
			STATUS	current
			::= { hmWanMbusF9 92 }

hmWanMbusF9Value2B		OBJECT-TYPE
			SYNTAX	INTEGER
			MAX-ACCESS	read-only
			STATUS	current
			::= { hmWanMbusF9 93 }

hmWanMbusF9VIF2C		OBJECT-TYPE
			SYNTAX	INTEGER
			MAX-ACCESS	read-only
			STATUS	current
			::= { hmWanMbusF9 94 }

hmWanMbusF9Value2C		OBJECT-TYPE
			SYNTAX	INTEGER
			MAX-ACCESS	read-only
			STATUS	current
			::= { hmWanMbusF9 95 }

hmWanMbusF9VIF2D		OBJECT-TYPE
			SYNTAX	INTEGER
			MAX-ACCESS	read-only
			STATUS	current
			::= { hmWanMbusF9 96 }

hmWanMbusF9Value2D		OBJECT-TYPE
			SYNTAX	INTEGER
			MAX-ACCESS	read-only
			STATUS	current
			::= { hmWanMbusF9 97 }

hmWanMbusF9VIF2E		OBJECT-TYPE
			SYNTAX	INTEGER
			MAX-ACCESS	read-only
			STATUS	current
			::= { hmWanMbusF9 98 }

hmWanMbusF9Value2E		OBJECT-TYPE
			SYNTAX	INTEGER
			MAX-ACCESS	read-only
			STATUS	current
			::= { hmWanMbusF9 99 }

hmWanMbusF9VIF2F		OBJECT-TYPE
			SYNTAX	INTEGER
			MAX-ACCESS	read-only
			STATUS	current
			::= { hmWanMbusF9 100 }

hmWanMbusF9Value2F		OBJECT-TYPE
			SYNTAX	INTEGER
			MAX-ACCESS	read-only
			STATUS	current
			::= { hmWanMbusF9 101 }

hmWanMbusFA			OBJECT IDENTIFIER ::= { hmWanMbus 250 }

hmWanMbusFAIdNumber		OBJECT-TYPE
			SYNTAX	Gauge32
			MAX-ACCESS	read-only
			STATUS	current
			::= { hmWanMbusFA 1 }

hmWanMbusFAManufacturer	OBJECT-TYPE
			SYNTAX	Gauge32
			MAX-ACCESS	read-only
			STATUS	current
			::= { hmWanMbusFA 2 }

hmWanMbusFAVersion		OBJECT-TYPE
			SYNTAX	Gauge32
			MAX-ACCESS	read-only
			STATUS	current
			::= { hmWanMbusFA 3 }

hmWanMbusFAMedium		OBJECT-TYPE
			SYNTAX	Gauge32
			MAX-ACCESS	read-only
			STATUS	current
			::= { hmWanMbusFA 4 }

hmWanMbusFAStatus		OBJECT-TYPE
			SYNTAX	Gauge32
			MAX-ACCESS	read-only
			STATUS	current
			::= { hmWanMbusFA 5 }

hmWanMbusFAVIF00		OBJECT-TYPE
			SYNTAX	INTEGER
			MAX-ACCESS	read-only
			STATUS	current
			::= { hmWanMbusFA 6 }

hmWanMbusFAValue00		OBJECT-TYPE
			SYNTAX	INTEGER
			MAX-ACCESS	read-only
			STATUS	current
			::= { hmWanMbusFA 7 }

hmWanMbusFAVIF01		OBJECT-TYPE
			SYNTAX	INTEGER
			MAX-ACCESS	read-only
			STATUS	current
			::= { hmWanMbusFA 8 }

hmWanMbusFAValue01		OBJECT-TYPE
			SYNTAX	INTEGER
			MAX-ACCESS	read-only
			STATUS	current
			::= { hmWanMbusFA 9 }

hmWanMbusFAVIF02		OBJECT-TYPE
			SYNTAX	INTEGER
			MAX-ACCESS	read-only
			STATUS	current
			::= { hmWanMbusFA 10 }

hmWanMbusFAValue02		OBJECT-TYPE
			SYNTAX	INTEGER
			MAX-ACCESS	read-only
			STATUS	current
			::= { hmWanMbusFA 11 }

hmWanMbusFAVIF03		OBJECT-TYPE
			SYNTAX	INTEGER
			MAX-ACCESS	read-only
			STATUS	current
			::= { hmWanMbusFA 12 }

hmWanMbusFAValue03		OBJECT-TYPE
			SYNTAX	INTEGER
			MAX-ACCESS	read-only
			STATUS	current
			::= { hmWanMbusFA 13 }

hmWanMbusFAVIF04		OBJECT-TYPE
			SYNTAX	INTEGER
			MAX-ACCESS	read-only
			STATUS	current
			::= { hmWanMbusFA 14 }

hmWanMbusFAValue04		OBJECT-TYPE
			SYNTAX	INTEGER
			MAX-ACCESS	read-only
			STATUS	current
			::= { hmWanMbusFA 15 }

hmWanMbusFAVIF05		OBJECT-TYPE
			SYNTAX	INTEGER
			MAX-ACCESS	read-only
			STATUS	current
			::= { hmWanMbusFA 16 }

hmWanMbusFAValue05		OBJECT-TYPE
			SYNTAX	INTEGER
			MAX-ACCESS	read-only
			STATUS	current
			::= { hmWanMbusFA 17 }

hmWanMbusFAVIF06		OBJECT-TYPE
			SYNTAX	INTEGER
			MAX-ACCESS	read-only
			STATUS	current
			::= { hmWanMbusFA 18 }

hmWanMbusFAValue06		OBJECT-TYPE
			SYNTAX	INTEGER
			MAX-ACCESS	read-only
			STATUS	current
			::= { hmWanMbusFA 19 }

hmWanMbusFAVIF07		OBJECT-TYPE
			SYNTAX	INTEGER
			MAX-ACCESS	read-only
			STATUS	current
			::= { hmWanMbusFA 20 }

hmWanMbusFAValue07		OBJECT-TYPE
			SYNTAX	INTEGER
			MAX-ACCESS	read-only
			STATUS	current
			::= { hmWanMbusFA 21 }

hmWanMbusFAVIF08		OBJECT-TYPE
			SYNTAX	INTEGER
			MAX-ACCESS	read-only
			STATUS	current
			::= { hmWanMbusFA 22 }

hmWanMbusFAValue08		OBJECT-TYPE
			SYNTAX	INTEGER
			MAX-ACCESS	read-only
			STATUS	current
			::= { hmWanMbusFA 23 }

hmWanMbusFAVIF09		OBJECT-TYPE
			SYNTAX	INTEGER
			MAX-ACCESS	read-only
			STATUS	current
			::= { hmWanMbusFA 24 }

hmWanMbusFAValue09		OBJECT-TYPE
			SYNTAX	INTEGER
			MAX-ACCESS	read-only
			STATUS	current
			::= { hmWanMbusFA 25 }

hmWanMbusFAVIF0A		OBJECT-TYPE
			SYNTAX	INTEGER
			MAX-ACCESS	read-only
			STATUS	current
			::= { hmWanMbusFA 26 }

hmWanMbusFAValue0A		OBJECT-TYPE
			SYNTAX	INTEGER
			MAX-ACCESS	read-only
			STATUS	current
			::= { hmWanMbusFA 27 }

hmWanMbusFAVIF0B		OBJECT-TYPE
			SYNTAX	INTEGER
			MAX-ACCESS	read-only
			STATUS	current
			::= { hmWanMbusFA 28 }

hmWanMbusFAValue0B		OBJECT-TYPE
			SYNTAX	INTEGER
			MAX-ACCESS	read-only
			STATUS	current
			::= { hmWanMbusFA 29 }

hmWanMbusFAVIF0C		OBJECT-TYPE
			SYNTAX	INTEGER
			MAX-ACCESS	read-only
			STATUS	current
			::= { hmWanMbusFA 30 }

hmWanMbusFAValue0C		OBJECT-TYPE
			SYNTAX	INTEGER
			MAX-ACCESS	read-only
			STATUS	current
			::= { hmWanMbusFA 31 }

hmWanMbusFAVIF0D		OBJECT-TYPE
			SYNTAX	INTEGER
			MAX-ACCESS	read-only
			STATUS	current
			::= { hmWanMbusFA 32 }

hmWanMbusFAValue0D		OBJECT-TYPE
			SYNTAX	INTEGER
			MAX-ACCESS	read-only
			STATUS	current
			::= { hmWanMbusFA 33 }

hmWanMbusFAVIF0E		OBJECT-TYPE
			SYNTAX	INTEGER
			MAX-ACCESS	read-only
			STATUS	current
			::= { hmWanMbusFA 34 }

hmWanMbusFAValue0E		OBJECT-TYPE
			SYNTAX	INTEGER
			MAX-ACCESS	read-only
			STATUS	current
			::= { hmWanMbusFA 35 }

hmWanMbusFAVIF0F		OBJECT-TYPE
			SYNTAX	INTEGER
			MAX-ACCESS	read-only
			STATUS	current
			::= { hmWanMbusFA 36 }

hmWanMbusFAValue0F		OBJECT-TYPE
			SYNTAX	INTEGER
			MAX-ACCESS	read-only
			STATUS	current
			::= { hmWanMbusFA 37 }

hmWanMbusFAVIF10		OBJECT-TYPE
			SYNTAX	INTEGER
			MAX-ACCESS	read-only
			STATUS	current
			::= { hmWanMbusFA 38 }

hmWanMbusFAValue10		OBJECT-TYPE
			SYNTAX	INTEGER
			MAX-ACCESS	read-only
			STATUS	current
			::= { hmWanMbusFA 39 }

hmWanMbusFAVIF11		OBJECT-TYPE
			SYNTAX	INTEGER
			MAX-ACCESS	read-only
			STATUS	current
			::= { hmWanMbusFA 40 }

hmWanMbusFAValue11		OBJECT-TYPE
			SYNTAX	INTEGER
			MAX-ACCESS	read-only
			STATUS	current
			::= { hmWanMbusFA 41 }

hmWanMbusFAVIF12		OBJECT-TYPE
			SYNTAX	INTEGER
			MAX-ACCESS	read-only
			STATUS	current
			::= { hmWanMbusFA 42 }

hmWanMbusFAValue12		OBJECT-TYPE
			SYNTAX	INTEGER
			MAX-ACCESS	read-only
			STATUS	current
			::= { hmWanMbusFA 43 }

hmWanMbusFAVIF13		OBJECT-TYPE
			SYNTAX	INTEGER
			MAX-ACCESS	read-only
			STATUS	current
			::= { hmWanMbusFA 44 }

hmWanMbusFAValue13		OBJECT-TYPE
			SYNTAX	INTEGER
			MAX-ACCESS	read-only
			STATUS	current
			::= { hmWanMbusFA 45 }

hmWanMbusFAVIF14		OBJECT-TYPE
			SYNTAX	INTEGER
			MAX-ACCESS	read-only
			STATUS	current
			::= { hmWanMbusFA 46 }

hmWanMbusFAValue14		OBJECT-TYPE
			SYNTAX	INTEGER
			MAX-ACCESS	read-only
			STATUS	current
			::= { hmWanMbusFA 47 }

hmWanMbusFAVIF15		OBJECT-TYPE
			SYNTAX	INTEGER
			MAX-ACCESS	read-only
			STATUS	current
			::= { hmWanMbusFA 48 }

hmWanMbusFAValue15		OBJECT-TYPE
			SYNTAX	INTEGER
			MAX-ACCESS	read-only
			STATUS	current
			::= { hmWanMbusFA 49 }

hmWanMbusFAVIF16		OBJECT-TYPE
			SYNTAX	INTEGER
			MAX-ACCESS	read-only
			STATUS	current
			::= { hmWanMbusFA 50 }

hmWanMbusFAValue16		OBJECT-TYPE
			SYNTAX	INTEGER
			MAX-ACCESS	read-only
			STATUS	current
			::= { hmWanMbusFA 51 }

hmWanMbusFAVIF17		OBJECT-TYPE
			SYNTAX	INTEGER
			MAX-ACCESS	read-only
			STATUS	current
			::= { hmWanMbusFA 52 }

hmWanMbusFAValue17		OBJECT-TYPE
			SYNTAX	INTEGER
			MAX-ACCESS	read-only
			STATUS	current
			::= { hmWanMbusFA 53 }

hmWanMbusFAVIF18		OBJECT-TYPE
			SYNTAX	INTEGER
			MAX-ACCESS	read-only
			STATUS	current
			::= { hmWanMbusFA 54 }

hmWanMbusFAValue18		OBJECT-TYPE
			SYNTAX	INTEGER
			MAX-ACCESS	read-only
			STATUS	current
			::= { hmWanMbusFA 55 }

hmWanMbusFAVIF19		OBJECT-TYPE
			SYNTAX	INTEGER
			MAX-ACCESS	read-only
			STATUS	current
			::= { hmWanMbusFA 56 }

hmWanMbusFAValue19		OBJECT-TYPE
			SYNTAX	INTEGER
			MAX-ACCESS	read-only
			STATUS	current
			::= { hmWanMbusFA 57 }

hmWanMbusFAVIF1A		OBJECT-TYPE
			SYNTAX	INTEGER
			MAX-ACCESS	read-only
			STATUS	current
			::= { hmWanMbusFA 58 }

hmWanMbusFAValue1A		OBJECT-TYPE
			SYNTAX	INTEGER
			MAX-ACCESS	read-only
			STATUS	current
			::= { hmWanMbusFA 59 }

hmWanMbusFAVIF1B		OBJECT-TYPE
			SYNTAX	INTEGER
			MAX-ACCESS	read-only
			STATUS	current
			::= { hmWanMbusFA 60 }

hmWanMbusFAValue1B		OBJECT-TYPE
			SYNTAX	INTEGER
			MAX-ACCESS	read-only
			STATUS	current
			::= { hmWanMbusFA 61 }

hmWanMbusFAVIF1C		OBJECT-TYPE
			SYNTAX	INTEGER
			MAX-ACCESS	read-only
			STATUS	current
			::= { hmWanMbusFA 62 }

hmWanMbusFAValue1C		OBJECT-TYPE
			SYNTAX	INTEGER
			MAX-ACCESS	read-only
			STATUS	current
			::= { hmWanMbusFA 63 }

hmWanMbusFAVIF1D		OBJECT-TYPE
			SYNTAX	INTEGER
			MAX-ACCESS	read-only
			STATUS	current
			::= { hmWanMbusFA 64 }

hmWanMbusFAValue1D		OBJECT-TYPE
			SYNTAX	INTEGER
			MAX-ACCESS	read-only
			STATUS	current
			::= { hmWanMbusFA 65 }

hmWanMbusFAVIF1E		OBJECT-TYPE
			SYNTAX	INTEGER
			MAX-ACCESS	read-only
			STATUS	current
			::= { hmWanMbusFA 66 }

hmWanMbusFAValue1E		OBJECT-TYPE
			SYNTAX	INTEGER
			MAX-ACCESS	read-only
			STATUS	current
			::= { hmWanMbusFA 67 }

hmWanMbusFAVIF1F		OBJECT-TYPE
			SYNTAX	INTEGER
			MAX-ACCESS	read-only
			STATUS	current
			::= { hmWanMbusFA 68 }

hmWanMbusFAValue1F		OBJECT-TYPE
			SYNTAX	INTEGER
			MAX-ACCESS	read-only
			STATUS	current
			::= { hmWanMbusFA 69 }

hmWanMbusFAVIF20		OBJECT-TYPE
			SYNTAX	INTEGER
			MAX-ACCESS	read-only
			STATUS	current
			::= { hmWanMbusFA 70 }

hmWanMbusFAValue20		OBJECT-TYPE
			SYNTAX	INTEGER
			MAX-ACCESS	read-only
			STATUS	current
			::= { hmWanMbusFA 71 }

hmWanMbusFAVIF21		OBJECT-TYPE
			SYNTAX	INTEGER
			MAX-ACCESS	read-only
			STATUS	current
			::= { hmWanMbusFA 72 }

hmWanMbusFAValue21		OBJECT-TYPE
			SYNTAX	INTEGER
			MAX-ACCESS	read-only
			STATUS	current
			::= { hmWanMbusFA 73 }

hmWanMbusFAVIF22		OBJECT-TYPE
			SYNTAX	INTEGER
			MAX-ACCESS	read-only
			STATUS	current
			::= { hmWanMbusFA 74 }

hmWanMbusFAValue22		OBJECT-TYPE
			SYNTAX	INTEGER
			MAX-ACCESS	read-only
			STATUS	current
			::= { hmWanMbusFA 75 }

hmWanMbusFAVIF23		OBJECT-TYPE
			SYNTAX	INTEGER
			MAX-ACCESS	read-only
			STATUS	current
			::= { hmWanMbusFA 76 }

hmWanMbusFAValue23		OBJECT-TYPE
			SYNTAX	INTEGER
			MAX-ACCESS	read-only
			STATUS	current
			::= { hmWanMbusFA 77 }

hmWanMbusFAVIF24		OBJECT-TYPE
			SYNTAX	INTEGER
			MAX-ACCESS	read-only
			STATUS	current
			::= { hmWanMbusFA 78 }

hmWanMbusFAValue24		OBJECT-TYPE
			SYNTAX	INTEGER
			MAX-ACCESS	read-only
			STATUS	current
			::= { hmWanMbusFA 79 }

hmWanMbusFAVIF25		OBJECT-TYPE
			SYNTAX	INTEGER
			MAX-ACCESS	read-only
			STATUS	current
			::= { hmWanMbusFA 80 }

hmWanMbusFAValue25		OBJECT-TYPE
			SYNTAX	INTEGER
			MAX-ACCESS	read-only
			STATUS	current
			::= { hmWanMbusFA 81 }

hmWanMbusFAVIF26		OBJECT-TYPE
			SYNTAX	INTEGER
			MAX-ACCESS	read-only
			STATUS	current
			::= { hmWanMbusFA 82 }

hmWanMbusFAValue26		OBJECT-TYPE
			SYNTAX	INTEGER
			MAX-ACCESS	read-only
			STATUS	current
			::= { hmWanMbusFA 83 }

hmWanMbusFAVIF27		OBJECT-TYPE
			SYNTAX	INTEGER
			MAX-ACCESS	read-only
			STATUS	current
			::= { hmWanMbusFA 84 }

hmWanMbusFAValue27		OBJECT-TYPE
			SYNTAX	INTEGER
			MAX-ACCESS	read-only
			STATUS	current
			::= { hmWanMbusFA 85 }

hmWanMbusFAVIF28		OBJECT-TYPE
			SYNTAX	INTEGER
			MAX-ACCESS	read-only
			STATUS	current
			::= { hmWanMbusFA 86 }

hmWanMbusFAValue28		OBJECT-TYPE
			SYNTAX	INTEGER
			MAX-ACCESS	read-only
			STATUS	current
			::= { hmWanMbusFA 87 }

hmWanMbusFAVIF29		OBJECT-TYPE
			SYNTAX	INTEGER
			MAX-ACCESS	read-only
			STATUS	current
			::= { hmWanMbusFA 88 }

hmWanMbusFAValue29		OBJECT-TYPE
			SYNTAX	INTEGER
			MAX-ACCESS	read-only
			STATUS	current
			::= { hmWanMbusFA 89 }

hmWanMbusFAVIF2A		OBJECT-TYPE
			SYNTAX	INTEGER
			MAX-ACCESS	read-only
			STATUS	current
			::= { hmWanMbusFA 90 }

hmWanMbusFAValue2A		OBJECT-TYPE
			SYNTAX	INTEGER
			MAX-ACCESS	read-only
			STATUS	current
			::= { hmWanMbusFA 91 }

hmWanMbusFAVIF2B		OBJECT-TYPE
			SYNTAX	INTEGER
			MAX-ACCESS	read-only
			STATUS	current
			::= { hmWanMbusFA 92 }

hmWanMbusFAValue2B		OBJECT-TYPE
			SYNTAX	INTEGER
			MAX-ACCESS	read-only
			STATUS	current
			::= { hmWanMbusFA 93 }

hmWanMbusFAVIF2C		OBJECT-TYPE
			SYNTAX	INTEGER
			MAX-ACCESS	read-only
			STATUS	current
			::= { hmWanMbusFA 94 }

hmWanMbusFAValue2C		OBJECT-TYPE
			SYNTAX	INTEGER
			MAX-ACCESS	read-only
			STATUS	current
			::= { hmWanMbusFA 95 }

hmWanMbusFAVIF2D		OBJECT-TYPE
			SYNTAX	INTEGER
			MAX-ACCESS	read-only
			STATUS	current
			::= { hmWanMbusFA 96 }

hmWanMbusFAValue2D		OBJECT-TYPE
			SYNTAX	INTEGER
			MAX-ACCESS	read-only
			STATUS	current
			::= { hmWanMbusFA 97 }

hmWanMbusFAVIF2E		OBJECT-TYPE
			SYNTAX	INTEGER
			MAX-ACCESS	read-only
			STATUS	current
			::= { hmWanMbusFA 98 }

hmWanMbusFAValue2E		OBJECT-TYPE
			SYNTAX	INTEGER
			MAX-ACCESS	read-only
			STATUS	current
			::= { hmWanMbusFA 99 }

hmWanMbusFAVIF2F		OBJECT-TYPE
			SYNTAX	INTEGER
			MAX-ACCESS	read-only
			STATUS	current
			::= { hmWanMbusFA 100 }

hmWanMbusFAValue2F		OBJECT-TYPE
			SYNTAX	INTEGER
			MAX-ACCESS	read-only
			STATUS	current
			::= { hmWanMbusFA 101 }

hmWanMbusFB			OBJECT IDENTIFIER ::= { hmWanMbus 251 }

hmWanMbusFBIdNumber		OBJECT-TYPE
			SYNTAX	Gauge32
			MAX-ACCESS	read-only
			STATUS	current
			::= { hmWanMbusFB 1 }

hmWanMbusFBManufacturer	OBJECT-TYPE
			SYNTAX	Gauge32
			MAX-ACCESS	read-only
			STATUS	current
			::= { hmWanMbusFB 2 }

hmWanMbusFBVersion		OBJECT-TYPE
			SYNTAX	Gauge32
			MAX-ACCESS	read-only
			STATUS	current
			::= { hmWanMbusFB 3 }

hmWanMbusFBMedium		OBJECT-TYPE
			SYNTAX	Gauge32
			MAX-ACCESS	read-only
			STATUS	current
			::= { hmWanMbusFB 4 }

hmWanMbusFBStatus		OBJECT-TYPE
			SYNTAX	Gauge32
			MAX-ACCESS	read-only
			STATUS	current
			::= { hmWanMbusFB 5 }

hmWanMbusFBVIF00		OBJECT-TYPE
			SYNTAX	INTEGER
			MAX-ACCESS	read-only
			STATUS	current
			::= { hmWanMbusFB 6 }

hmWanMbusFBValue00		OBJECT-TYPE
			SYNTAX	INTEGER
			MAX-ACCESS	read-only
			STATUS	current
			::= { hmWanMbusFB 7 }

hmWanMbusFBVIF01		OBJECT-TYPE
			SYNTAX	INTEGER
			MAX-ACCESS	read-only
			STATUS	current
			::= { hmWanMbusFB 8 }

hmWanMbusFBValue01		OBJECT-TYPE
			SYNTAX	INTEGER
			MAX-ACCESS	read-only
			STATUS	current
			::= { hmWanMbusFB 9 }

hmWanMbusFBVIF02		OBJECT-TYPE
			SYNTAX	INTEGER
			MAX-ACCESS	read-only
			STATUS	current
			::= { hmWanMbusFB 10 }

hmWanMbusFBValue02		OBJECT-TYPE
			SYNTAX	INTEGER
			MAX-ACCESS	read-only
			STATUS	current
			::= { hmWanMbusFB 11 }

hmWanMbusFBVIF03		OBJECT-TYPE
			SYNTAX	INTEGER
			MAX-ACCESS	read-only
			STATUS	current
			::= { hmWanMbusFB 12 }

hmWanMbusFBValue03		OBJECT-TYPE
			SYNTAX	INTEGER
			MAX-ACCESS	read-only
			STATUS	current
			::= { hmWanMbusFB 13 }

hmWanMbusFBVIF04		OBJECT-TYPE
			SYNTAX	INTEGER
			MAX-ACCESS	read-only
			STATUS	current
			::= { hmWanMbusFB 14 }

hmWanMbusFBValue04		OBJECT-TYPE
			SYNTAX	INTEGER
			MAX-ACCESS	read-only
			STATUS	current
			::= { hmWanMbusFB 15 }

hmWanMbusFBVIF05		OBJECT-TYPE
			SYNTAX	INTEGER
			MAX-ACCESS	read-only
			STATUS	current
			::= { hmWanMbusFB 16 }

hmWanMbusFBValue05		OBJECT-TYPE
			SYNTAX	INTEGER
			MAX-ACCESS	read-only
			STATUS	current
			::= { hmWanMbusFB 17 }

hmWanMbusFBVIF06		OBJECT-TYPE
			SYNTAX	INTEGER
			MAX-ACCESS	read-only
			STATUS	current
			::= { hmWanMbusFB 18 }

hmWanMbusFBValue06		OBJECT-TYPE
			SYNTAX	INTEGER
			MAX-ACCESS	read-only
			STATUS	current
			::= { hmWanMbusFB 19 }

hmWanMbusFBVIF07		OBJECT-TYPE
			SYNTAX	INTEGER
			MAX-ACCESS	read-only
			STATUS	current
			::= { hmWanMbusFB 20 }

hmWanMbusFBValue07		OBJECT-TYPE
			SYNTAX	INTEGER
			MAX-ACCESS	read-only
			STATUS	current
			::= { hmWanMbusFB 21 }

hmWanMbusFBVIF08		OBJECT-TYPE
			SYNTAX	INTEGER
			MAX-ACCESS	read-only
			STATUS	current
			::= { hmWanMbusFB 22 }

hmWanMbusFBValue08		OBJECT-TYPE
			SYNTAX	INTEGER
			MAX-ACCESS	read-only
			STATUS	current
			::= { hmWanMbusFB 23 }

hmWanMbusFBVIF09		OBJECT-TYPE
			SYNTAX	INTEGER
			MAX-ACCESS	read-only
			STATUS	current
			::= { hmWanMbusFB 24 }

hmWanMbusFBValue09		OBJECT-TYPE
			SYNTAX	INTEGER
			MAX-ACCESS	read-only
			STATUS	current
			::= { hmWanMbusFB 25 }

hmWanMbusFBVIF0A		OBJECT-TYPE
			SYNTAX	INTEGER
			MAX-ACCESS	read-only
			STATUS	current
			::= { hmWanMbusFB 26 }

hmWanMbusFBValue0A		OBJECT-TYPE
			SYNTAX	INTEGER
			MAX-ACCESS	read-only
			STATUS	current
			::= { hmWanMbusFB 27 }

hmWanMbusFBVIF0B		OBJECT-TYPE
			SYNTAX	INTEGER
			MAX-ACCESS	read-only
			STATUS	current
			::= { hmWanMbusFB 28 }

hmWanMbusFBValue0B		OBJECT-TYPE
			SYNTAX	INTEGER
			MAX-ACCESS	read-only
			STATUS	current
			::= { hmWanMbusFB 29 }

hmWanMbusFBVIF0C		OBJECT-TYPE
			SYNTAX	INTEGER
			MAX-ACCESS	read-only
			STATUS	current
			::= { hmWanMbusFB 30 }

hmWanMbusFBValue0C		OBJECT-TYPE
			SYNTAX	INTEGER
			MAX-ACCESS	read-only
			STATUS	current
			::= { hmWanMbusFB 31 }

hmWanMbusFBVIF0D		OBJECT-TYPE
			SYNTAX	INTEGER
			MAX-ACCESS	read-only
			STATUS	current
			::= { hmWanMbusFB 32 }

hmWanMbusFBValue0D		OBJECT-TYPE
			SYNTAX	INTEGER
			MAX-ACCESS	read-only
			STATUS	current
			::= { hmWanMbusFB 33 }

hmWanMbusFBVIF0E		OBJECT-TYPE
			SYNTAX	INTEGER
			MAX-ACCESS	read-only
			STATUS	current
			::= { hmWanMbusFB 34 }

hmWanMbusFBValue0E		OBJECT-TYPE
			SYNTAX	INTEGER
			MAX-ACCESS	read-only
			STATUS	current
			::= { hmWanMbusFB 35 }

hmWanMbusFBVIF0F		OBJECT-TYPE
			SYNTAX	INTEGER
			MAX-ACCESS	read-only
			STATUS	current
			::= { hmWanMbusFB 36 }

hmWanMbusFBValue0F		OBJECT-TYPE
			SYNTAX	INTEGER
			MAX-ACCESS	read-only
			STATUS	current
			::= { hmWanMbusFB 37 }

hmWanMbusFBVIF10		OBJECT-TYPE
			SYNTAX	INTEGER
			MAX-ACCESS	read-only
			STATUS	current
			::= { hmWanMbusFB 38 }

hmWanMbusFBValue10		OBJECT-TYPE
			SYNTAX	INTEGER
			MAX-ACCESS	read-only
			STATUS	current
			::= { hmWanMbusFB 39 }

hmWanMbusFBVIF11		OBJECT-TYPE
			SYNTAX	INTEGER
			MAX-ACCESS	read-only
			STATUS	current
			::= { hmWanMbusFB 40 }

hmWanMbusFBValue11		OBJECT-TYPE
			SYNTAX	INTEGER
			MAX-ACCESS	read-only
			STATUS	current
			::= { hmWanMbusFB 41 }

hmWanMbusFBVIF12		OBJECT-TYPE
			SYNTAX	INTEGER
			MAX-ACCESS	read-only
			STATUS	current
			::= { hmWanMbusFB 42 }

hmWanMbusFBValue12		OBJECT-TYPE
			SYNTAX	INTEGER
			MAX-ACCESS	read-only
			STATUS	current
			::= { hmWanMbusFB 43 }

hmWanMbusFBVIF13		OBJECT-TYPE
			SYNTAX	INTEGER
			MAX-ACCESS	read-only
			STATUS	current
			::= { hmWanMbusFB 44 }

hmWanMbusFBValue13		OBJECT-TYPE
			SYNTAX	INTEGER
			MAX-ACCESS	read-only
			STATUS	current
			::= { hmWanMbusFB 45 }

hmWanMbusFBVIF14		OBJECT-TYPE
			SYNTAX	INTEGER
			MAX-ACCESS	read-only
			STATUS	current
			::= { hmWanMbusFB 46 }

hmWanMbusFBValue14		OBJECT-TYPE
			SYNTAX	INTEGER
			MAX-ACCESS	read-only
			STATUS	current
			::= { hmWanMbusFB 47 }

hmWanMbusFBVIF15		OBJECT-TYPE
			SYNTAX	INTEGER
			MAX-ACCESS	read-only
			STATUS	current
			::= { hmWanMbusFB 48 }

hmWanMbusFBValue15		OBJECT-TYPE
			SYNTAX	INTEGER
			MAX-ACCESS	read-only
			STATUS	current
			::= { hmWanMbusFB 49 }

hmWanMbusFBVIF16		OBJECT-TYPE
			SYNTAX	INTEGER
			MAX-ACCESS	read-only
			STATUS	current
			::= { hmWanMbusFB 50 }

hmWanMbusFBValue16		OBJECT-TYPE
			SYNTAX	INTEGER
			MAX-ACCESS	read-only
			STATUS	current
			::= { hmWanMbusFB 51 }

hmWanMbusFBVIF17		OBJECT-TYPE
			SYNTAX	INTEGER
			MAX-ACCESS	read-only
			STATUS	current
			::= { hmWanMbusFB 52 }

hmWanMbusFBValue17		OBJECT-TYPE
			SYNTAX	INTEGER
			MAX-ACCESS	read-only
			STATUS	current
			::= { hmWanMbusFB 53 }

hmWanMbusFBVIF18		OBJECT-TYPE
			SYNTAX	INTEGER
			MAX-ACCESS	read-only
			STATUS	current
			::= { hmWanMbusFB 54 }

hmWanMbusFBValue18		OBJECT-TYPE
			SYNTAX	INTEGER
			MAX-ACCESS	read-only
			STATUS	current
			::= { hmWanMbusFB 55 }

hmWanMbusFBVIF19		OBJECT-TYPE
			SYNTAX	INTEGER
			MAX-ACCESS	read-only
			STATUS	current
			::= { hmWanMbusFB 56 }

hmWanMbusFBValue19		OBJECT-TYPE
			SYNTAX	INTEGER
			MAX-ACCESS	read-only
			STATUS	current
			::= { hmWanMbusFB 57 }

hmWanMbusFBVIF1A		OBJECT-TYPE
			SYNTAX	INTEGER
			MAX-ACCESS	read-only
			STATUS	current
			::= { hmWanMbusFB 58 }

hmWanMbusFBValue1A		OBJECT-TYPE
			SYNTAX	INTEGER
			MAX-ACCESS	read-only
			STATUS	current
			::= { hmWanMbusFB 59 }

hmWanMbusFBVIF1B		OBJECT-TYPE
			SYNTAX	INTEGER
			MAX-ACCESS	read-only
			STATUS	current
			::= { hmWanMbusFB 60 }

hmWanMbusFBValue1B		OBJECT-TYPE
			SYNTAX	INTEGER
			MAX-ACCESS	read-only
			STATUS	current
			::= { hmWanMbusFB 61 }

hmWanMbusFBVIF1C		OBJECT-TYPE
			SYNTAX	INTEGER
			MAX-ACCESS	read-only
			STATUS	current
			::= { hmWanMbusFB 62 }

hmWanMbusFBValue1C		OBJECT-TYPE
			SYNTAX	INTEGER
			MAX-ACCESS	read-only
			STATUS	current
			::= { hmWanMbusFB 63 }

hmWanMbusFBVIF1D		OBJECT-TYPE
			SYNTAX	INTEGER
			MAX-ACCESS	read-only
			STATUS	current
			::= { hmWanMbusFB 64 }

hmWanMbusFBValue1D		OBJECT-TYPE
			SYNTAX	INTEGER
			MAX-ACCESS	read-only
			STATUS	current
			::= { hmWanMbusFB 65 }

hmWanMbusFBVIF1E		OBJECT-TYPE
			SYNTAX	INTEGER
			MAX-ACCESS	read-only
			STATUS	current
			::= { hmWanMbusFB 66 }

hmWanMbusFBValue1E		OBJECT-TYPE
			SYNTAX	INTEGER
			MAX-ACCESS	read-only
			STATUS	current
			::= { hmWanMbusFB 67 }

hmWanMbusFBVIF1F		OBJECT-TYPE
			SYNTAX	INTEGER
			MAX-ACCESS	read-only
			STATUS	current
			::= { hmWanMbusFB 68 }

hmWanMbusFBValue1F		OBJECT-TYPE
			SYNTAX	INTEGER
			MAX-ACCESS	read-only
			STATUS	current
			::= { hmWanMbusFB 69 }

hmWanMbusFBVIF20		OBJECT-TYPE
			SYNTAX	INTEGER
			MAX-ACCESS	read-only
			STATUS	current
			::= { hmWanMbusFB 70 }

hmWanMbusFBValue20		OBJECT-TYPE
			SYNTAX	INTEGER
			MAX-ACCESS	read-only
			STATUS	current
			::= { hmWanMbusFB 71 }

hmWanMbusFBVIF21		OBJECT-TYPE
			SYNTAX	INTEGER
			MAX-ACCESS	read-only
			STATUS	current
			::= { hmWanMbusFB 72 }

hmWanMbusFBValue21		OBJECT-TYPE
			SYNTAX	INTEGER
			MAX-ACCESS	read-only
			STATUS	current
			::= { hmWanMbusFB 73 }

hmWanMbusFBVIF22		OBJECT-TYPE
			SYNTAX	INTEGER
			MAX-ACCESS	read-only
			STATUS	current
			::= { hmWanMbusFB 74 }

hmWanMbusFBValue22		OBJECT-TYPE
			SYNTAX	INTEGER
			MAX-ACCESS	read-only
			STATUS	current
			::= { hmWanMbusFB 75 }

hmWanMbusFBVIF23		OBJECT-TYPE
			SYNTAX	INTEGER
			MAX-ACCESS	read-only
			STATUS	current
			::= { hmWanMbusFB 76 }

hmWanMbusFBValue23		OBJECT-TYPE
			SYNTAX	INTEGER
			MAX-ACCESS	read-only
			STATUS	current
			::= { hmWanMbusFB 77 }

hmWanMbusFBVIF24		OBJECT-TYPE
			SYNTAX	INTEGER
			MAX-ACCESS	read-only
			STATUS	current
			::= { hmWanMbusFB 78 }

hmWanMbusFBValue24		OBJECT-TYPE
			SYNTAX	INTEGER
			MAX-ACCESS	read-only
			STATUS	current
			::= { hmWanMbusFB 79 }

hmWanMbusFBVIF25		OBJECT-TYPE
			SYNTAX	INTEGER
			MAX-ACCESS	read-only
			STATUS	current
			::= { hmWanMbusFB 80 }

hmWanMbusFBValue25		OBJECT-TYPE
			SYNTAX	INTEGER
			MAX-ACCESS	read-only
			STATUS	current
			::= { hmWanMbusFB 81 }

hmWanMbusFBVIF26		OBJECT-TYPE
			SYNTAX	INTEGER
			MAX-ACCESS	read-only
			STATUS	current
			::= { hmWanMbusFB 82 }

hmWanMbusFBValue26		OBJECT-TYPE
			SYNTAX	INTEGER
			MAX-ACCESS	read-only
			STATUS	current
			::= { hmWanMbusFB 83 }

hmWanMbusFBVIF27		OBJECT-TYPE
			SYNTAX	INTEGER
			MAX-ACCESS	read-only
			STATUS	current
			::= { hmWanMbusFB 84 }

hmWanMbusFBValue27		OBJECT-TYPE
			SYNTAX	INTEGER
			MAX-ACCESS	read-only
			STATUS	current
			::= { hmWanMbusFB 85 }

hmWanMbusFBVIF28		OBJECT-TYPE
			SYNTAX	INTEGER
			MAX-ACCESS	read-only
			STATUS	current
			::= { hmWanMbusFB 86 }

hmWanMbusFBValue28		OBJECT-TYPE
			SYNTAX	INTEGER
			MAX-ACCESS	read-only
			STATUS	current
			::= { hmWanMbusFB 87 }

hmWanMbusFBVIF29		OBJECT-TYPE
			SYNTAX	INTEGER
			MAX-ACCESS	read-only
			STATUS	current
			::= { hmWanMbusFB 88 }

hmWanMbusFBValue29		OBJECT-TYPE
			SYNTAX	INTEGER
			MAX-ACCESS	read-only
			STATUS	current
			::= { hmWanMbusFB 89 }

hmWanMbusFBVIF2A		OBJECT-TYPE
			SYNTAX	INTEGER
			MAX-ACCESS	read-only
			STATUS	current
			::= { hmWanMbusFB 90 }

hmWanMbusFBValue2A		OBJECT-TYPE
			SYNTAX	INTEGER
			MAX-ACCESS	read-only
			STATUS	current
			::= { hmWanMbusFB 91 }

hmWanMbusFBVIF2B		OBJECT-TYPE
			SYNTAX	INTEGER
			MAX-ACCESS	read-only
			STATUS	current
			::= { hmWanMbusFB 92 }

hmWanMbusFBValue2B		OBJECT-TYPE
			SYNTAX	INTEGER
			MAX-ACCESS	read-only
			STATUS	current
			::= { hmWanMbusFB 93 }

hmWanMbusFBVIF2C		OBJECT-TYPE
			SYNTAX	INTEGER
			MAX-ACCESS	read-only
			STATUS	current
			::= { hmWanMbusFB 94 }

hmWanMbusFBValue2C		OBJECT-TYPE
			SYNTAX	INTEGER
			MAX-ACCESS	read-only
			STATUS	current
			::= { hmWanMbusFB 95 }

hmWanMbusFBVIF2D		OBJECT-TYPE
			SYNTAX	INTEGER
			MAX-ACCESS	read-only
			STATUS	current
			::= { hmWanMbusFB 96 }

hmWanMbusFBValue2D		OBJECT-TYPE
			SYNTAX	INTEGER
			MAX-ACCESS	read-only
			STATUS	current
			::= { hmWanMbusFB 97 }

hmWanMbusFBVIF2E		OBJECT-TYPE
			SYNTAX	INTEGER
			MAX-ACCESS	read-only
			STATUS	current
			::= { hmWanMbusFB 98 }

hmWanMbusFBValue2E		OBJECT-TYPE
			SYNTAX	INTEGER
			MAX-ACCESS	read-only
			STATUS	current
			::= { hmWanMbusFB 99 }

hmWanMbusFBVIF2F		OBJECT-TYPE
			SYNTAX	INTEGER
			MAX-ACCESS	read-only
			STATUS	current
			::= { hmWanMbusFB 100 }

hmWanMbusFBValue2F		OBJECT-TYPE
			SYNTAX	INTEGER
			MAX-ACCESS	read-only
			STATUS	current
			::= { hmWanMbusFB 101 }

hmWanMbusFC			OBJECT IDENTIFIER ::= { hmWanMbus 252 }

hmWanMbusFCIdNumber		OBJECT-TYPE
			SYNTAX	Gauge32
			MAX-ACCESS	read-only
			STATUS	current
			::= { hmWanMbusFC 1 }

hmWanMbusFCManufacturer	OBJECT-TYPE
			SYNTAX	Gauge32
			MAX-ACCESS	read-only
			STATUS	current
			::= { hmWanMbusFC 2 }

hmWanMbusFCVersion		OBJECT-TYPE
			SYNTAX	Gauge32
			MAX-ACCESS	read-only
			STATUS	current
			::= { hmWanMbusFC 3 }

hmWanMbusFCMedium		OBJECT-TYPE
			SYNTAX	Gauge32
			MAX-ACCESS	read-only
			STATUS	current
			::= { hmWanMbusFC 4 }

hmWanMbusFCStatus		OBJECT-TYPE
			SYNTAX	Gauge32
			MAX-ACCESS	read-only
			STATUS	current
			::= { hmWanMbusFC 5 }

hmWanMbusFCVIF00		OBJECT-TYPE
			SYNTAX	INTEGER
			MAX-ACCESS	read-only
			STATUS	current
			::= { hmWanMbusFC 6 }

hmWanMbusFCValue00		OBJECT-TYPE
			SYNTAX	INTEGER
			MAX-ACCESS	read-only
			STATUS	current
			::= { hmWanMbusFC 7 }

hmWanMbusFCVIF01		OBJECT-TYPE
			SYNTAX	INTEGER
			MAX-ACCESS	read-only
			STATUS	current
			::= { hmWanMbusFC 8 }

hmWanMbusFCValue01		OBJECT-TYPE
			SYNTAX	INTEGER
			MAX-ACCESS	read-only
			STATUS	current
			::= { hmWanMbusFC 9 }

hmWanMbusFCVIF02		OBJECT-TYPE
			SYNTAX	INTEGER
			MAX-ACCESS	read-only
			STATUS	current
			::= { hmWanMbusFC 10 }

hmWanMbusFCValue02		OBJECT-TYPE
			SYNTAX	INTEGER
			MAX-ACCESS	read-only
			STATUS	current
			::= { hmWanMbusFC 11 }

hmWanMbusFCVIF03		OBJECT-TYPE
			SYNTAX	INTEGER
			MAX-ACCESS	read-only
			STATUS	current
			::= { hmWanMbusFC 12 }

hmWanMbusFCValue03		OBJECT-TYPE
			SYNTAX	INTEGER
			MAX-ACCESS	read-only
			STATUS	current
			::= { hmWanMbusFC 13 }

hmWanMbusFCVIF04		OBJECT-TYPE
			SYNTAX	INTEGER
			MAX-ACCESS	read-only
			STATUS	current
			::= { hmWanMbusFC 14 }

hmWanMbusFCValue04		OBJECT-TYPE
			SYNTAX	INTEGER
			MAX-ACCESS	read-only
			STATUS	current
			::= { hmWanMbusFC 15 }

hmWanMbusFCVIF05		OBJECT-TYPE
			SYNTAX	INTEGER
			MAX-ACCESS	read-only
			STATUS	current
			::= { hmWanMbusFC 16 }

hmWanMbusFCValue05		OBJECT-TYPE
			SYNTAX	INTEGER
			MAX-ACCESS	read-only
			STATUS	current
			::= { hmWanMbusFC 17 }

hmWanMbusFCVIF06		OBJECT-TYPE
			SYNTAX	INTEGER
			MAX-ACCESS	read-only
			STATUS	current
			::= { hmWanMbusFC 18 }

hmWanMbusFCValue06		OBJECT-TYPE
			SYNTAX	INTEGER
			MAX-ACCESS	read-only
			STATUS	current
			::= { hmWanMbusFC 19 }

hmWanMbusFCVIF07		OBJECT-TYPE
			SYNTAX	INTEGER
			MAX-ACCESS	read-only
			STATUS	current
			::= { hmWanMbusFC 20 }

hmWanMbusFCValue07		OBJECT-TYPE
			SYNTAX	INTEGER
			MAX-ACCESS	read-only
			STATUS	current
			::= { hmWanMbusFC 21 }

hmWanMbusFCVIF08		OBJECT-TYPE
			SYNTAX	INTEGER
			MAX-ACCESS	read-only
			STATUS	current
			::= { hmWanMbusFC 22 }

hmWanMbusFCValue08		OBJECT-TYPE
			SYNTAX	INTEGER
			MAX-ACCESS	read-only
			STATUS	current
			::= { hmWanMbusFC 23 }

hmWanMbusFCVIF09		OBJECT-TYPE
			SYNTAX	INTEGER
			MAX-ACCESS	read-only
			STATUS	current
			::= { hmWanMbusFC 24 }

hmWanMbusFCValue09		OBJECT-TYPE
			SYNTAX	INTEGER
			MAX-ACCESS	read-only
			STATUS	current
			::= { hmWanMbusFC 25 }

hmWanMbusFCVIF0A		OBJECT-TYPE
			SYNTAX	INTEGER
			MAX-ACCESS	read-only
			STATUS	current
			::= { hmWanMbusFC 26 }

hmWanMbusFCValue0A		OBJECT-TYPE
			SYNTAX	INTEGER
			MAX-ACCESS	read-only
			STATUS	current
			::= { hmWanMbusFC 27 }

hmWanMbusFCVIF0B		OBJECT-TYPE
			SYNTAX	INTEGER
			MAX-ACCESS	read-only
			STATUS	current
			::= { hmWanMbusFC 28 }

hmWanMbusFCValue0B		OBJECT-TYPE
			SYNTAX	INTEGER
			MAX-ACCESS	read-only
			STATUS	current
			::= { hmWanMbusFC 29 }

hmWanMbusFCVIF0C		OBJECT-TYPE
			SYNTAX	INTEGER
			MAX-ACCESS	read-only
			STATUS	current
			::= { hmWanMbusFC 30 }

hmWanMbusFCValue0C		OBJECT-TYPE
			SYNTAX	INTEGER
			MAX-ACCESS	read-only
			STATUS	current
			::= { hmWanMbusFC 31 }

hmWanMbusFCVIF0D		OBJECT-TYPE
			SYNTAX	INTEGER
			MAX-ACCESS	read-only
			STATUS	current
			::= { hmWanMbusFC 32 }

hmWanMbusFCValue0D		OBJECT-TYPE
			SYNTAX	INTEGER
			MAX-ACCESS	read-only
			STATUS	current
			::= { hmWanMbusFC 33 }

hmWanMbusFCVIF0E		OBJECT-TYPE
			SYNTAX	INTEGER
			MAX-ACCESS	read-only
			STATUS	current
			::= { hmWanMbusFC 34 }

hmWanMbusFCValue0E		OBJECT-TYPE
			SYNTAX	INTEGER
			MAX-ACCESS	read-only
			STATUS	current
			::= { hmWanMbusFC 35 }

hmWanMbusFCVIF0F		OBJECT-TYPE
			SYNTAX	INTEGER
			MAX-ACCESS	read-only
			STATUS	current
			::= { hmWanMbusFC 36 }

hmWanMbusFCValue0F		OBJECT-TYPE
			SYNTAX	INTEGER
			MAX-ACCESS	read-only
			STATUS	current
			::= { hmWanMbusFC 37 }

hmWanMbusFCVIF10		OBJECT-TYPE
			SYNTAX	INTEGER
			MAX-ACCESS	read-only
			STATUS	current
			::= { hmWanMbusFC 38 }

hmWanMbusFCValue10		OBJECT-TYPE
			SYNTAX	INTEGER
			MAX-ACCESS	read-only
			STATUS	current
			::= { hmWanMbusFC 39 }

hmWanMbusFCVIF11		OBJECT-TYPE
			SYNTAX	INTEGER
			MAX-ACCESS	read-only
			STATUS	current
			::= { hmWanMbusFC 40 }

hmWanMbusFCValue11		OBJECT-TYPE
			SYNTAX	INTEGER
			MAX-ACCESS	read-only
			STATUS	current
			::= { hmWanMbusFC 41 }

hmWanMbusFCVIF12		OBJECT-TYPE
			SYNTAX	INTEGER
			MAX-ACCESS	read-only
			STATUS	current
			::= { hmWanMbusFC 42 }

hmWanMbusFCValue12		OBJECT-TYPE
			SYNTAX	INTEGER
			MAX-ACCESS	read-only
			STATUS	current
			::= { hmWanMbusFC 43 }

hmWanMbusFCVIF13		OBJECT-TYPE
			SYNTAX	INTEGER
			MAX-ACCESS	read-only
			STATUS	current
			::= { hmWanMbusFC 44 }

hmWanMbusFCValue13		OBJECT-TYPE
			SYNTAX	INTEGER
			MAX-ACCESS	read-only
			STATUS	current
			::= { hmWanMbusFC 45 }

hmWanMbusFCVIF14		OBJECT-TYPE
			SYNTAX	INTEGER
			MAX-ACCESS	read-only
			STATUS	current
			::= { hmWanMbusFC 46 }

hmWanMbusFCValue14		OBJECT-TYPE
			SYNTAX	INTEGER
			MAX-ACCESS	read-only
			STATUS	current
			::= { hmWanMbusFC 47 }

hmWanMbusFCVIF15		OBJECT-TYPE
			SYNTAX	INTEGER
			MAX-ACCESS	read-only
			STATUS	current
			::= { hmWanMbusFC 48 }

hmWanMbusFCValue15		OBJECT-TYPE
			SYNTAX	INTEGER
			MAX-ACCESS	read-only
			STATUS	current
			::= { hmWanMbusFC 49 }

hmWanMbusFCVIF16		OBJECT-TYPE
			SYNTAX	INTEGER
			MAX-ACCESS	read-only
			STATUS	current
			::= { hmWanMbusFC 50 }

hmWanMbusFCValue16		OBJECT-TYPE
			SYNTAX	INTEGER
			MAX-ACCESS	read-only
			STATUS	current
			::= { hmWanMbusFC 51 }

hmWanMbusFCVIF17		OBJECT-TYPE
			SYNTAX	INTEGER
			MAX-ACCESS	read-only
			STATUS	current
			::= { hmWanMbusFC 52 }

hmWanMbusFCValue17		OBJECT-TYPE
			SYNTAX	INTEGER
			MAX-ACCESS	read-only
			STATUS	current
			::= { hmWanMbusFC 53 }

hmWanMbusFCVIF18		OBJECT-TYPE
			SYNTAX	INTEGER
			MAX-ACCESS	read-only
			STATUS	current
			::= { hmWanMbusFC 54 }

hmWanMbusFCValue18		OBJECT-TYPE
			SYNTAX	INTEGER
			MAX-ACCESS	read-only
			STATUS	current
			::= { hmWanMbusFC 55 }

hmWanMbusFCVIF19		OBJECT-TYPE
			SYNTAX	INTEGER
			MAX-ACCESS	read-only
			STATUS	current
			::= { hmWanMbusFC 56 }

hmWanMbusFCValue19		OBJECT-TYPE
			SYNTAX	INTEGER
			MAX-ACCESS	read-only
			STATUS	current
			::= { hmWanMbusFC 57 }

hmWanMbusFCVIF1A		OBJECT-TYPE
			SYNTAX	INTEGER
			MAX-ACCESS	read-only
			STATUS	current
			::= { hmWanMbusFC 58 }

hmWanMbusFCValue1A		OBJECT-TYPE
			SYNTAX	INTEGER
			MAX-ACCESS	read-only
			STATUS	current
			::= { hmWanMbusFC 59 }

hmWanMbusFCVIF1B		OBJECT-TYPE
			SYNTAX	INTEGER
			MAX-ACCESS	read-only
			STATUS	current
			::= { hmWanMbusFC 60 }

hmWanMbusFCValue1B		OBJECT-TYPE
			SYNTAX	INTEGER
			MAX-ACCESS	read-only
			STATUS	current
			::= { hmWanMbusFC 61 }

hmWanMbusFCVIF1C		OBJECT-TYPE
			SYNTAX	INTEGER
			MAX-ACCESS	read-only
			STATUS	current
			::= { hmWanMbusFC 62 }

hmWanMbusFCValue1C		OBJECT-TYPE
			SYNTAX	INTEGER
			MAX-ACCESS	read-only
			STATUS	current
			::= { hmWanMbusFC 63 }

hmWanMbusFCVIF1D		OBJECT-TYPE
			SYNTAX	INTEGER
			MAX-ACCESS	read-only
			STATUS	current
			::= { hmWanMbusFC 64 }

hmWanMbusFCValue1D		OBJECT-TYPE
			SYNTAX	INTEGER
			MAX-ACCESS	read-only
			STATUS	current
			::= { hmWanMbusFC 65 }

hmWanMbusFCVIF1E		OBJECT-TYPE
			SYNTAX	INTEGER
			MAX-ACCESS	read-only
			STATUS	current
			::= { hmWanMbusFC 66 }

hmWanMbusFCValue1E		OBJECT-TYPE
			SYNTAX	INTEGER
			MAX-ACCESS	read-only
			STATUS	current
			::= { hmWanMbusFC 67 }

hmWanMbusFCVIF1F		OBJECT-TYPE
			SYNTAX	INTEGER
			MAX-ACCESS	read-only
			STATUS	current
			::= { hmWanMbusFC 68 }

hmWanMbusFCValue1F		OBJECT-TYPE
			SYNTAX	INTEGER
			MAX-ACCESS	read-only
			STATUS	current
			::= { hmWanMbusFC 69 }

hmWanMbusFCVIF20		OBJECT-TYPE
			SYNTAX	INTEGER
			MAX-ACCESS	read-only
			STATUS	current
			::= { hmWanMbusFC 70 }

hmWanMbusFCValue20		OBJECT-TYPE
			SYNTAX	INTEGER
			MAX-ACCESS	read-only
			STATUS	current
			::= { hmWanMbusFC 71 }

hmWanMbusFCVIF21		OBJECT-TYPE
			SYNTAX	INTEGER
			MAX-ACCESS	read-only
			STATUS	current
			::= { hmWanMbusFC 72 }

hmWanMbusFCValue21		OBJECT-TYPE
			SYNTAX	INTEGER
			MAX-ACCESS	read-only
			STATUS	current
			::= { hmWanMbusFC 73 }

hmWanMbusFCVIF22		OBJECT-TYPE
			SYNTAX	INTEGER
			MAX-ACCESS	read-only
			STATUS	current
			::= { hmWanMbusFC 74 }

hmWanMbusFCValue22		OBJECT-TYPE
			SYNTAX	INTEGER
			MAX-ACCESS	read-only
			STATUS	current
			::= { hmWanMbusFC 75 }

hmWanMbusFCVIF23		OBJECT-TYPE
			SYNTAX	INTEGER
			MAX-ACCESS	read-only
			STATUS	current
			::= { hmWanMbusFC 76 }

hmWanMbusFCValue23		OBJECT-TYPE
			SYNTAX	INTEGER
			MAX-ACCESS	read-only
			STATUS	current
			::= { hmWanMbusFC 77 }

hmWanMbusFCVIF24		OBJECT-TYPE
			SYNTAX	INTEGER
			MAX-ACCESS	read-only
			STATUS	current
			::= { hmWanMbusFC 78 }

hmWanMbusFCValue24		OBJECT-TYPE
			SYNTAX	INTEGER
			MAX-ACCESS	read-only
			STATUS	current
			::= { hmWanMbusFC 79 }

hmWanMbusFCVIF25		OBJECT-TYPE
			SYNTAX	INTEGER
			MAX-ACCESS	read-only
			STATUS	current
			::= { hmWanMbusFC 80 }

hmWanMbusFCValue25		OBJECT-TYPE
			SYNTAX	INTEGER
			MAX-ACCESS	read-only
			STATUS	current
			::= { hmWanMbusFC 81 }

hmWanMbusFCVIF26		OBJECT-TYPE
			SYNTAX	INTEGER
			MAX-ACCESS	read-only
			STATUS	current
			::= { hmWanMbusFC 82 }

hmWanMbusFCValue26		OBJECT-TYPE
			SYNTAX	INTEGER
			MAX-ACCESS	read-only
			STATUS	current
			::= { hmWanMbusFC 83 }

hmWanMbusFCVIF27		OBJECT-TYPE
			SYNTAX	INTEGER
			MAX-ACCESS	read-only
			STATUS	current
			::= { hmWanMbusFC 84 }

hmWanMbusFCValue27		OBJECT-TYPE
			SYNTAX	INTEGER
			MAX-ACCESS	read-only
			STATUS	current
			::= { hmWanMbusFC 85 }

hmWanMbusFCVIF28		OBJECT-TYPE
			SYNTAX	INTEGER
			MAX-ACCESS	read-only
			STATUS	current
			::= { hmWanMbusFC 86 }

hmWanMbusFCValue28		OBJECT-TYPE
			SYNTAX	INTEGER
			MAX-ACCESS	read-only
			STATUS	current
			::= { hmWanMbusFC 87 }

hmWanMbusFCVIF29		OBJECT-TYPE
			SYNTAX	INTEGER
			MAX-ACCESS	read-only
			STATUS	current
			::= { hmWanMbusFC 88 }

hmWanMbusFCValue29		OBJECT-TYPE
			SYNTAX	INTEGER
			MAX-ACCESS	read-only
			STATUS	current
			::= { hmWanMbusFC 89 }

hmWanMbusFCVIF2A		OBJECT-TYPE
			SYNTAX	INTEGER
			MAX-ACCESS	read-only
			STATUS	current
			::= { hmWanMbusFC 90 }

hmWanMbusFCValue2A		OBJECT-TYPE
			SYNTAX	INTEGER
			MAX-ACCESS	read-only
			STATUS	current
			::= { hmWanMbusFC 91 }

hmWanMbusFCVIF2B		OBJECT-TYPE
			SYNTAX	INTEGER
			MAX-ACCESS	read-only
			STATUS	current
			::= { hmWanMbusFC 92 }

hmWanMbusFCValue2B		OBJECT-TYPE
			SYNTAX	INTEGER
			MAX-ACCESS	read-only
			STATUS	current
			::= { hmWanMbusFC 93 }

hmWanMbusFCVIF2C		OBJECT-TYPE
			SYNTAX	INTEGER
			MAX-ACCESS	read-only
			STATUS	current
			::= { hmWanMbusFC 94 }

hmWanMbusFCValue2C		OBJECT-TYPE
			SYNTAX	INTEGER
			MAX-ACCESS	read-only
			STATUS	current
			::= { hmWanMbusFC 95 }

hmWanMbusFCVIF2D		OBJECT-TYPE
			SYNTAX	INTEGER
			MAX-ACCESS	read-only
			STATUS	current
			::= { hmWanMbusFC 96 }

hmWanMbusFCValue2D		OBJECT-TYPE
			SYNTAX	INTEGER
			MAX-ACCESS	read-only
			STATUS	current
			::= { hmWanMbusFC 97 }

hmWanMbusFCVIF2E		OBJECT-TYPE
			SYNTAX	INTEGER
			MAX-ACCESS	read-only
			STATUS	current
			::= { hmWanMbusFC 98 }

hmWanMbusFCValue2E		OBJECT-TYPE
			SYNTAX	INTEGER
			MAX-ACCESS	read-only
			STATUS	current
			::= { hmWanMbusFC 99 }

hmWanMbusFCVIF2F		OBJECT-TYPE
			SYNTAX	INTEGER
			MAX-ACCESS	read-only
			STATUS	current
			::= { hmWanMbusFC 100 }

hmWanMbusFCValue2F		OBJECT-TYPE
			SYNTAX	INTEGER
			MAX-ACCESS	read-only
			STATUS	current
			::= { hmWanMbusFC 101 }

hmWanMbusFD			OBJECT IDENTIFIER ::= { hmWanMbus 253 }

hmWanMbusFDIdNumber		OBJECT-TYPE
			SYNTAX	Gauge32
			MAX-ACCESS	read-only
			STATUS	current
			::= { hmWanMbusFD 1 }

hmWanMbusFDManufacturer	OBJECT-TYPE
			SYNTAX	Gauge32
			MAX-ACCESS	read-only
			STATUS	current
			::= { hmWanMbusFD 2 }

hmWanMbusFDVersion		OBJECT-TYPE
			SYNTAX	Gauge32
			MAX-ACCESS	read-only
			STATUS	current
			::= { hmWanMbusFD 3 }

hmWanMbusFDMedium		OBJECT-TYPE
			SYNTAX	Gauge32
			MAX-ACCESS	read-only
			STATUS	current
			::= { hmWanMbusFD 4 }

hmWanMbusFDStatus		OBJECT-TYPE
			SYNTAX	Gauge32
			MAX-ACCESS	read-only
			STATUS	current
			::= { hmWanMbusFD 5 }

hmWanMbusFDVIF00		OBJECT-TYPE
			SYNTAX	INTEGER
			MAX-ACCESS	read-only
			STATUS	current
			::= { hmWanMbusFD 6 }

hmWanMbusFDValue00		OBJECT-TYPE
			SYNTAX	INTEGER
			MAX-ACCESS	read-only
			STATUS	current
			::= { hmWanMbusFD 7 }

hmWanMbusFDVIF01		OBJECT-TYPE
			SYNTAX	INTEGER
			MAX-ACCESS	read-only
			STATUS	current
			::= { hmWanMbusFD 8 }

hmWanMbusFDValue01		OBJECT-TYPE
			SYNTAX	INTEGER
			MAX-ACCESS	read-only
			STATUS	current
			::= { hmWanMbusFD 9 }

hmWanMbusFDVIF02		OBJECT-TYPE
			SYNTAX	INTEGER
			MAX-ACCESS	read-only
			STATUS	current
			::= { hmWanMbusFD 10 }

hmWanMbusFDValue02		OBJECT-TYPE
			SYNTAX	INTEGER
			MAX-ACCESS	read-only
			STATUS	current
			::= { hmWanMbusFD 11 }

hmWanMbusFDVIF03		OBJECT-TYPE
			SYNTAX	INTEGER
			MAX-ACCESS	read-only
			STATUS	current
			::= { hmWanMbusFD 12 }

hmWanMbusFDValue03		OBJECT-TYPE
			SYNTAX	INTEGER
			MAX-ACCESS	read-only
			STATUS	current
			::= { hmWanMbusFD 13 }

hmWanMbusFDVIF04		OBJECT-TYPE
			SYNTAX	INTEGER
			MAX-ACCESS	read-only
			STATUS	current
			::= { hmWanMbusFD 14 }

hmWanMbusFDValue04		OBJECT-TYPE
			SYNTAX	INTEGER
			MAX-ACCESS	read-only
			STATUS	current
			::= { hmWanMbusFD 15 }

hmWanMbusFDVIF05		OBJECT-TYPE
			SYNTAX	INTEGER
			MAX-ACCESS	read-only
			STATUS	current
			::= { hmWanMbusFD 16 }

hmWanMbusFDValue05		OBJECT-TYPE
			SYNTAX	INTEGER
			MAX-ACCESS	read-only
			STATUS	current
			::= { hmWanMbusFD 17 }

hmWanMbusFDVIF06		OBJECT-TYPE
			SYNTAX	INTEGER
			MAX-ACCESS	read-only
			STATUS	current
			::= { hmWanMbusFD 18 }

hmWanMbusFDValue06		OBJECT-TYPE
			SYNTAX	INTEGER
			MAX-ACCESS	read-only
			STATUS	current
			::= { hmWanMbusFD 19 }

hmWanMbusFDVIF07		OBJECT-TYPE
			SYNTAX	INTEGER
			MAX-ACCESS	read-only
			STATUS	current
			::= { hmWanMbusFD 20 }

hmWanMbusFDValue07		OBJECT-TYPE
			SYNTAX	INTEGER
			MAX-ACCESS	read-only
			STATUS	current
			::= { hmWanMbusFD 21 }

hmWanMbusFDVIF08		OBJECT-TYPE
			SYNTAX	INTEGER
			MAX-ACCESS	read-only
			STATUS	current
			::= { hmWanMbusFD 22 }

hmWanMbusFDValue08		OBJECT-TYPE
			SYNTAX	INTEGER
			MAX-ACCESS	read-only
			STATUS	current
			::= { hmWanMbusFD 23 }

hmWanMbusFDVIF09		OBJECT-TYPE
			SYNTAX	INTEGER
			MAX-ACCESS	read-only
			STATUS	current
			::= { hmWanMbusFD 24 }

hmWanMbusFDValue09		OBJECT-TYPE
			SYNTAX	INTEGER
			MAX-ACCESS	read-only
			STATUS	current
			::= { hmWanMbusFD 25 }

hmWanMbusFDVIF0A		OBJECT-TYPE
			SYNTAX	INTEGER
			MAX-ACCESS	read-only
			STATUS	current
			::= { hmWanMbusFD 26 }

hmWanMbusFDValue0A		OBJECT-TYPE
			SYNTAX	INTEGER
			MAX-ACCESS	read-only
			STATUS	current
			::= { hmWanMbusFD 27 }

hmWanMbusFDVIF0B		OBJECT-TYPE
			SYNTAX	INTEGER
			MAX-ACCESS	read-only
			STATUS	current
			::= { hmWanMbusFD 28 }

hmWanMbusFDValue0B		OBJECT-TYPE
			SYNTAX	INTEGER
			MAX-ACCESS	read-only
			STATUS	current
			::= { hmWanMbusFD 29 }

hmWanMbusFDVIF0C		OBJECT-TYPE
			SYNTAX	INTEGER
			MAX-ACCESS	read-only
			STATUS	current
			::= { hmWanMbusFD 30 }

hmWanMbusFDValue0C		OBJECT-TYPE
			SYNTAX	INTEGER
			MAX-ACCESS	read-only
			STATUS	current
			::= { hmWanMbusFD 31 }

hmWanMbusFDVIF0D		OBJECT-TYPE
			SYNTAX	INTEGER
			MAX-ACCESS	read-only
			STATUS	current
			::= { hmWanMbusFD 32 }

hmWanMbusFDValue0D		OBJECT-TYPE
			SYNTAX	INTEGER
			MAX-ACCESS	read-only
			STATUS	current
			::= { hmWanMbusFD 33 }

hmWanMbusFDVIF0E		OBJECT-TYPE
			SYNTAX	INTEGER
			MAX-ACCESS	read-only
			STATUS	current
			::= { hmWanMbusFD 34 }

hmWanMbusFDValue0E		OBJECT-TYPE
			SYNTAX	INTEGER
			MAX-ACCESS	read-only
			STATUS	current
			::= { hmWanMbusFD 35 }

hmWanMbusFDVIF0F		OBJECT-TYPE
			SYNTAX	INTEGER
			MAX-ACCESS	read-only
			STATUS	current
			::= { hmWanMbusFD 36 }

hmWanMbusFDValue0F		OBJECT-TYPE
			SYNTAX	INTEGER
			MAX-ACCESS	read-only
			STATUS	current
			::= { hmWanMbusFD 37 }

hmWanMbusFDVIF10		OBJECT-TYPE
			SYNTAX	INTEGER
			MAX-ACCESS	read-only
			STATUS	current
			::= { hmWanMbusFD 38 }

hmWanMbusFDValue10		OBJECT-TYPE
			SYNTAX	INTEGER
			MAX-ACCESS	read-only
			STATUS	current
			::= { hmWanMbusFD 39 }

hmWanMbusFDVIF11		OBJECT-TYPE
			SYNTAX	INTEGER
			MAX-ACCESS	read-only
			STATUS	current
			::= { hmWanMbusFD 40 }

hmWanMbusFDValue11		OBJECT-TYPE
			SYNTAX	INTEGER
			MAX-ACCESS	read-only
			STATUS	current
			::= { hmWanMbusFD 41 }

hmWanMbusFDVIF12		OBJECT-TYPE
			SYNTAX	INTEGER
			MAX-ACCESS	read-only
			STATUS	current
			::= { hmWanMbusFD 42 }

hmWanMbusFDValue12		OBJECT-TYPE
			SYNTAX	INTEGER
			MAX-ACCESS	read-only
			STATUS	current
			::= { hmWanMbusFD 43 }

hmWanMbusFDVIF13		OBJECT-TYPE
			SYNTAX	INTEGER
			MAX-ACCESS	read-only
			STATUS	current
			::= { hmWanMbusFD 44 }

hmWanMbusFDValue13		OBJECT-TYPE
			SYNTAX	INTEGER
			MAX-ACCESS	read-only
			STATUS	current
			::= { hmWanMbusFD 45 }

hmWanMbusFDVIF14		OBJECT-TYPE
			SYNTAX	INTEGER
			MAX-ACCESS	read-only
			STATUS	current
			::= { hmWanMbusFD 46 }

hmWanMbusFDValue14		OBJECT-TYPE
			SYNTAX	INTEGER
			MAX-ACCESS	read-only
			STATUS	current
			::= { hmWanMbusFD 47 }

hmWanMbusFDVIF15		OBJECT-TYPE
			SYNTAX	INTEGER
			MAX-ACCESS	read-only
			STATUS	current
			::= { hmWanMbusFD 48 }

hmWanMbusFDValue15		OBJECT-TYPE
			SYNTAX	INTEGER
			MAX-ACCESS	read-only
			STATUS	current
			::= { hmWanMbusFD 49 }

hmWanMbusFDVIF16		OBJECT-TYPE
			SYNTAX	INTEGER
			MAX-ACCESS	read-only
			STATUS	current
			::= { hmWanMbusFD 50 }

hmWanMbusFDValue16		OBJECT-TYPE
			SYNTAX	INTEGER
			MAX-ACCESS	read-only
			STATUS	current
			::= { hmWanMbusFD 51 }

hmWanMbusFDVIF17		OBJECT-TYPE
			SYNTAX	INTEGER
			MAX-ACCESS	read-only
			STATUS	current
			::= { hmWanMbusFD 52 }

hmWanMbusFDValue17		OBJECT-TYPE
			SYNTAX	INTEGER
			MAX-ACCESS	read-only
			STATUS	current
			::= { hmWanMbusFD 53 }

hmWanMbusFDVIF18		OBJECT-TYPE
			SYNTAX	INTEGER
			MAX-ACCESS	read-only
			STATUS	current
			::= { hmWanMbusFD 54 }

hmWanMbusFDValue18		OBJECT-TYPE
			SYNTAX	INTEGER
			MAX-ACCESS	read-only
			STATUS	current
			::= { hmWanMbusFD 55 }

hmWanMbusFDVIF19		OBJECT-TYPE
			SYNTAX	INTEGER
			MAX-ACCESS	read-only
			STATUS	current
			::= { hmWanMbusFD 56 }

hmWanMbusFDValue19		OBJECT-TYPE
			SYNTAX	INTEGER
			MAX-ACCESS	read-only
			STATUS	current
			::= { hmWanMbusFD 57 }

hmWanMbusFDVIF1A		OBJECT-TYPE
			SYNTAX	INTEGER
			MAX-ACCESS	read-only
			STATUS	current
			::= { hmWanMbusFD 58 }

hmWanMbusFDValue1A		OBJECT-TYPE
			SYNTAX	INTEGER
			MAX-ACCESS	read-only
			STATUS	current
			::= { hmWanMbusFD 59 }

hmWanMbusFDVIF1B		OBJECT-TYPE
			SYNTAX	INTEGER
			MAX-ACCESS	read-only
			STATUS	current
			::= { hmWanMbusFD 60 }

hmWanMbusFDValue1B		OBJECT-TYPE
			SYNTAX	INTEGER
			MAX-ACCESS	read-only
			STATUS	current
			::= { hmWanMbusFD 61 }

hmWanMbusFDVIF1C		OBJECT-TYPE
			SYNTAX	INTEGER
			MAX-ACCESS	read-only
			STATUS	current
			::= { hmWanMbusFD 62 }

hmWanMbusFDValue1C		OBJECT-TYPE
			SYNTAX	INTEGER
			MAX-ACCESS	read-only
			STATUS	current
			::= { hmWanMbusFD 63 }

hmWanMbusFDVIF1D		OBJECT-TYPE
			SYNTAX	INTEGER
			MAX-ACCESS	read-only
			STATUS	current
			::= { hmWanMbusFD 64 }

hmWanMbusFDValue1D		OBJECT-TYPE
			SYNTAX	INTEGER
			MAX-ACCESS	read-only
			STATUS	current
			::= { hmWanMbusFD 65 }

hmWanMbusFDVIF1E		OBJECT-TYPE
			SYNTAX	INTEGER
			MAX-ACCESS	read-only
			STATUS	current
			::= { hmWanMbusFD 66 }

hmWanMbusFDValue1E		OBJECT-TYPE
			SYNTAX	INTEGER
			MAX-ACCESS	read-only
			STATUS	current
			::= { hmWanMbusFD 67 }

hmWanMbusFDVIF1F		OBJECT-TYPE
			SYNTAX	INTEGER
			MAX-ACCESS	read-only
			STATUS	current
			::= { hmWanMbusFD 68 }

hmWanMbusFDValue1F		OBJECT-TYPE
			SYNTAX	INTEGER
			MAX-ACCESS	read-only
			STATUS	current
			::= { hmWanMbusFD 69 }

hmWanMbusFDVIF20		OBJECT-TYPE
			SYNTAX	INTEGER
			MAX-ACCESS	read-only
			STATUS	current
			::= { hmWanMbusFD 70 }

hmWanMbusFDValue20		OBJECT-TYPE
			SYNTAX	INTEGER
			MAX-ACCESS	read-only
			STATUS	current
			::= { hmWanMbusFD 71 }

hmWanMbusFDVIF21		OBJECT-TYPE
			SYNTAX	INTEGER
			MAX-ACCESS	read-only
			STATUS	current
			::= { hmWanMbusFD 72 }

hmWanMbusFDValue21		OBJECT-TYPE
			SYNTAX	INTEGER
			MAX-ACCESS	read-only
			STATUS	current
			::= { hmWanMbusFD 73 }

hmWanMbusFDVIF22		OBJECT-TYPE
			SYNTAX	INTEGER
			MAX-ACCESS	read-only
			STATUS	current
			::= { hmWanMbusFD 74 }

hmWanMbusFDValue22		OBJECT-TYPE
			SYNTAX	INTEGER
			MAX-ACCESS	read-only
			STATUS	current
			::= { hmWanMbusFD 75 }

hmWanMbusFDVIF23		OBJECT-TYPE
			SYNTAX	INTEGER
			MAX-ACCESS	read-only
			STATUS	current
			::= { hmWanMbusFD 76 }

hmWanMbusFDValue23		OBJECT-TYPE
			SYNTAX	INTEGER
			MAX-ACCESS	read-only
			STATUS	current
			::= { hmWanMbusFD 77 }

hmWanMbusFDVIF24		OBJECT-TYPE
			SYNTAX	INTEGER
			MAX-ACCESS	read-only
			STATUS	current
			::= { hmWanMbusFD 78 }

hmWanMbusFDValue24		OBJECT-TYPE
			SYNTAX	INTEGER
			MAX-ACCESS	read-only
			STATUS	current
			::= { hmWanMbusFD 79 }

hmWanMbusFDVIF25		OBJECT-TYPE
			SYNTAX	INTEGER
			MAX-ACCESS	read-only
			STATUS	current
			::= { hmWanMbusFD 80 }

hmWanMbusFDValue25		OBJECT-TYPE
			SYNTAX	INTEGER
			MAX-ACCESS	read-only
			STATUS	current
			::= { hmWanMbusFD 81 }

hmWanMbusFDVIF26		OBJECT-TYPE
			SYNTAX	INTEGER
			MAX-ACCESS	read-only
			STATUS	current
			::= { hmWanMbusFD 82 }

hmWanMbusFDValue26		OBJECT-TYPE
			SYNTAX	INTEGER
			MAX-ACCESS	read-only
			STATUS	current
			::= { hmWanMbusFD 83 }

hmWanMbusFDVIF27		OBJECT-TYPE
			SYNTAX	INTEGER
			MAX-ACCESS	read-only
			STATUS	current
			::= { hmWanMbusFD 84 }

hmWanMbusFDValue27		OBJECT-TYPE
			SYNTAX	INTEGER
			MAX-ACCESS	read-only
			STATUS	current
			::= { hmWanMbusFD 85 }

hmWanMbusFDVIF28		OBJECT-TYPE
			SYNTAX	INTEGER
			MAX-ACCESS	read-only
			STATUS	current
			::= { hmWanMbusFD 86 }

hmWanMbusFDValue28		OBJECT-TYPE
			SYNTAX	INTEGER
			MAX-ACCESS	read-only
			STATUS	current
			::= { hmWanMbusFD 87 }

hmWanMbusFDVIF29		OBJECT-TYPE
			SYNTAX	INTEGER
			MAX-ACCESS	read-only
			STATUS	current
			::= { hmWanMbusFD 88 }

hmWanMbusFDValue29		OBJECT-TYPE
			SYNTAX	INTEGER
			MAX-ACCESS	read-only
			STATUS	current
			::= { hmWanMbusFD 89 }

hmWanMbusFDVIF2A		OBJECT-TYPE
			SYNTAX	INTEGER
			MAX-ACCESS	read-only
			STATUS	current
			::= { hmWanMbusFD 90 }

hmWanMbusFDValue2A		OBJECT-TYPE
			SYNTAX	INTEGER
			MAX-ACCESS	read-only
			STATUS	current
			::= { hmWanMbusFD 91 }

hmWanMbusFDVIF2B		OBJECT-TYPE
			SYNTAX	INTEGER
			MAX-ACCESS	read-only
			STATUS	current
			::= { hmWanMbusFD 92 }

hmWanMbusFDValue2B		OBJECT-TYPE
			SYNTAX	INTEGER
			MAX-ACCESS	read-only
			STATUS	current
			::= { hmWanMbusFD 93 }

hmWanMbusFDVIF2C		OBJECT-TYPE
			SYNTAX	INTEGER
			MAX-ACCESS	read-only
			STATUS	current
			::= { hmWanMbusFD 94 }

hmWanMbusFDValue2C		OBJECT-TYPE
			SYNTAX	INTEGER
			MAX-ACCESS	read-only
			STATUS	current
			::= { hmWanMbusFD 95 }

hmWanMbusFDVIF2D		OBJECT-TYPE
			SYNTAX	INTEGER
			MAX-ACCESS	read-only
			STATUS	current
			::= { hmWanMbusFD 96 }

hmWanMbusFDValue2D		OBJECT-TYPE
			SYNTAX	INTEGER
			MAX-ACCESS	read-only
			STATUS	current
			::= { hmWanMbusFD 97 }

hmWanMbusFDVIF2E		OBJECT-TYPE
			SYNTAX	INTEGER
			MAX-ACCESS	read-only
			STATUS	current
			::= { hmWanMbusFD 98 }

hmWanMbusFDValue2E		OBJECT-TYPE
			SYNTAX	INTEGER
			MAX-ACCESS	read-only
			STATUS	current
			::= { hmWanMbusFD 99 }

hmWanMbusFDVIF2F		OBJECT-TYPE
			SYNTAX	INTEGER
			MAX-ACCESS	read-only
			STATUS	current
			::= { hmWanMbusFD 100 }

hmWanMbusFDValue2F		OBJECT-TYPE
			SYNTAX	INTEGER
			MAX-ACCESS	read-only
			STATUS	current
			::= { hmWanMbusFD 101 }

hmWanMbusFE			OBJECT IDENTIFIER ::= { hmWanMbus 254 }

hmWanMbusFEIdNumber		OBJECT-TYPE
			SYNTAX	Gauge32
			MAX-ACCESS	read-only
			STATUS	current
			::= { hmWanMbusFE 1 }

hmWanMbusFEManufacturer	OBJECT-TYPE
			SYNTAX	Gauge32
			MAX-ACCESS	read-only
			STATUS	current
			::= { hmWanMbusFE 2 }

hmWanMbusFEVersion		OBJECT-TYPE
			SYNTAX	Gauge32
			MAX-ACCESS	read-only
			STATUS	current
			::= { hmWanMbusFE 3 }

hmWanMbusFEMedium		OBJECT-TYPE
			SYNTAX	Gauge32
			MAX-ACCESS	read-only
			STATUS	current
			::= { hmWanMbusFE 4 }

hmWanMbusFEStatus		OBJECT-TYPE
			SYNTAX	Gauge32
			MAX-ACCESS	read-only
			STATUS	current
			::= { hmWanMbusFE 5 }

hmWanMbusFEVIF00		OBJECT-TYPE
			SYNTAX	INTEGER
			MAX-ACCESS	read-only
			STATUS	current
			::= { hmWanMbusFE 6 }

hmWanMbusFEValue00		OBJECT-TYPE
			SYNTAX	INTEGER
			MAX-ACCESS	read-only
			STATUS	current
			::= { hmWanMbusFE 7 }

hmWanMbusFEVIF01		OBJECT-TYPE
			SYNTAX	INTEGER
			MAX-ACCESS	read-only
			STATUS	current
			::= { hmWanMbusFE 8 }

hmWanMbusFEValue01		OBJECT-TYPE
			SYNTAX	INTEGER
			MAX-ACCESS	read-only
			STATUS	current
			::= { hmWanMbusFE 9 }

hmWanMbusFEVIF02		OBJECT-TYPE
			SYNTAX	INTEGER
			MAX-ACCESS	read-only
			STATUS	current
			::= { hmWanMbusFE 10 }

hmWanMbusFEValue02		OBJECT-TYPE
			SYNTAX	INTEGER
			MAX-ACCESS	read-only
			STATUS	current
			::= { hmWanMbusFE 11 }

hmWanMbusFEVIF03		OBJECT-TYPE
			SYNTAX	INTEGER
			MAX-ACCESS	read-only
			STATUS	current
			::= { hmWanMbusFE 12 }

hmWanMbusFEValue03		OBJECT-TYPE
			SYNTAX	INTEGER
			MAX-ACCESS	read-only
			STATUS	current
			::= { hmWanMbusFE 13 }

hmWanMbusFEVIF04		OBJECT-TYPE
			SYNTAX	INTEGER
			MAX-ACCESS	read-only
			STATUS	current
			::= { hmWanMbusFE 14 }

hmWanMbusFEValue04		OBJECT-TYPE
			SYNTAX	INTEGER
			MAX-ACCESS	read-only
			STATUS	current
			::= { hmWanMbusFE 15 }

hmWanMbusFEVIF05		OBJECT-TYPE
			SYNTAX	INTEGER
			MAX-ACCESS	read-only
			STATUS	current
			::= { hmWanMbusFE 16 }

hmWanMbusFEValue05		OBJECT-TYPE
			SYNTAX	INTEGER
			MAX-ACCESS	read-only
			STATUS	current
			::= { hmWanMbusFE 17 }

hmWanMbusFEVIF06		OBJECT-TYPE
			SYNTAX	INTEGER
			MAX-ACCESS	read-only
			STATUS	current
			::= { hmWanMbusFE 18 }

hmWanMbusFEValue06		OBJECT-TYPE
			SYNTAX	INTEGER
			MAX-ACCESS	read-only
			STATUS	current
			::= { hmWanMbusFE 19 }

hmWanMbusFEVIF07		OBJECT-TYPE
			SYNTAX	INTEGER
			MAX-ACCESS	read-only
			STATUS	current
			::= { hmWanMbusFE 20 }

hmWanMbusFEValue07		OBJECT-TYPE
			SYNTAX	INTEGER
			MAX-ACCESS	read-only
			STATUS	current
			::= { hmWanMbusFE 21 }

hmWanMbusFEVIF08		OBJECT-TYPE
			SYNTAX	INTEGER
			MAX-ACCESS	read-only
			STATUS	current
			::= { hmWanMbusFE 22 }

hmWanMbusFEValue08		OBJECT-TYPE
			SYNTAX	INTEGER
			MAX-ACCESS	read-only
			STATUS	current
			::= { hmWanMbusFE 23 }

hmWanMbusFEVIF09		OBJECT-TYPE
			SYNTAX	INTEGER
			MAX-ACCESS	read-only
			STATUS	current
			::= { hmWanMbusFE 24 }

hmWanMbusFEValue09		OBJECT-TYPE
			SYNTAX	INTEGER
			MAX-ACCESS	read-only
			STATUS	current
			::= { hmWanMbusFE 25 }

hmWanMbusFEVIF0A		OBJECT-TYPE
			SYNTAX	INTEGER
			MAX-ACCESS	read-only
			STATUS	current
			::= { hmWanMbusFE 26 }

hmWanMbusFEValue0A		OBJECT-TYPE
			SYNTAX	INTEGER
			MAX-ACCESS	read-only
			STATUS	current
			::= { hmWanMbusFE 27 }

hmWanMbusFEVIF0B		OBJECT-TYPE
			SYNTAX	INTEGER
			MAX-ACCESS	read-only
			STATUS	current
			::= { hmWanMbusFE 28 }

hmWanMbusFEValue0B		OBJECT-TYPE
			SYNTAX	INTEGER
			MAX-ACCESS	read-only
			STATUS	current
			::= { hmWanMbusFE 29 }

hmWanMbusFEVIF0C		OBJECT-TYPE
			SYNTAX	INTEGER
			MAX-ACCESS	read-only
			STATUS	current
			::= { hmWanMbusFE 30 }

hmWanMbusFEValue0C		OBJECT-TYPE
			SYNTAX	INTEGER
			MAX-ACCESS	read-only
			STATUS	current
			::= { hmWanMbusFE 31 }

hmWanMbusFEVIF0D		OBJECT-TYPE
			SYNTAX	INTEGER
			MAX-ACCESS	read-only
			STATUS	current
			::= { hmWanMbusFE 32 }

hmWanMbusFEValue0D		OBJECT-TYPE
			SYNTAX	INTEGER
			MAX-ACCESS	read-only
			STATUS	current
			::= { hmWanMbusFE 33 }

hmWanMbusFEVIF0E		OBJECT-TYPE
			SYNTAX	INTEGER
			MAX-ACCESS	read-only
			STATUS	current
			::= { hmWanMbusFE 34 }

hmWanMbusFEValue0E		OBJECT-TYPE
			SYNTAX	INTEGER
			MAX-ACCESS	read-only
			STATUS	current
			::= { hmWanMbusFE 35 }

hmWanMbusFEVIF0F		OBJECT-TYPE
			SYNTAX	INTEGER
			MAX-ACCESS	read-only
			STATUS	current
			::= { hmWanMbusFE 36 }

hmWanMbusFEValue0F		OBJECT-TYPE
			SYNTAX	INTEGER
			MAX-ACCESS	read-only
			STATUS	current
			::= { hmWanMbusFE 37 }

hmWanMbusFEVIF10		OBJECT-TYPE
			SYNTAX	INTEGER
			MAX-ACCESS	read-only
			STATUS	current
			::= { hmWanMbusFE 38 }

hmWanMbusFEValue10		OBJECT-TYPE
			SYNTAX	INTEGER
			MAX-ACCESS	read-only
			STATUS	current
			::= { hmWanMbusFE 39 }

hmWanMbusFEVIF11		OBJECT-TYPE
			SYNTAX	INTEGER
			MAX-ACCESS	read-only
			STATUS	current
			::= { hmWanMbusFE 40 }

hmWanMbusFEValue11		OBJECT-TYPE
			SYNTAX	INTEGER
			MAX-ACCESS	read-only
			STATUS	current
			::= { hmWanMbusFE 41 }

hmWanMbusFEVIF12		OBJECT-TYPE
			SYNTAX	INTEGER
			MAX-ACCESS	read-only
			STATUS	current
			::= { hmWanMbusFE 42 }

hmWanMbusFEValue12		OBJECT-TYPE
			SYNTAX	INTEGER
			MAX-ACCESS	read-only
			STATUS	current
			::= { hmWanMbusFE 43 }

hmWanMbusFEVIF13		OBJECT-TYPE
			SYNTAX	INTEGER
			MAX-ACCESS	read-only
			STATUS	current
			::= { hmWanMbusFE 44 }

hmWanMbusFEValue13		OBJECT-TYPE
			SYNTAX	INTEGER
			MAX-ACCESS	read-only
			STATUS	current
			::= { hmWanMbusFE 45 }

hmWanMbusFEVIF14		OBJECT-TYPE
			SYNTAX	INTEGER
			MAX-ACCESS	read-only
			STATUS	current
			::= { hmWanMbusFE 46 }

hmWanMbusFEValue14		OBJECT-TYPE
			SYNTAX	INTEGER
			MAX-ACCESS	read-only
			STATUS	current
			::= { hmWanMbusFE 47 }

hmWanMbusFEVIF15		OBJECT-TYPE
			SYNTAX	INTEGER
			MAX-ACCESS	read-only
			STATUS	current
			::= { hmWanMbusFE 48 }

hmWanMbusFEValue15		OBJECT-TYPE
			SYNTAX	INTEGER
			MAX-ACCESS	read-only
			STATUS	current
			::= { hmWanMbusFE 49 }

hmWanMbusFEVIF16		OBJECT-TYPE
			SYNTAX	INTEGER
			MAX-ACCESS	read-only
			STATUS	current
			::= { hmWanMbusFE 50 }

hmWanMbusFEValue16		OBJECT-TYPE
			SYNTAX	INTEGER
			MAX-ACCESS	read-only
			STATUS	current
			::= { hmWanMbusFE 51 }

hmWanMbusFEVIF17		OBJECT-TYPE
			SYNTAX	INTEGER
			MAX-ACCESS	read-only
			STATUS	current
			::= { hmWanMbusFE 52 }

hmWanMbusFEValue17		OBJECT-TYPE
			SYNTAX	INTEGER
			MAX-ACCESS	read-only
			STATUS	current
			::= { hmWanMbusFE 53 }

hmWanMbusFEVIF18		OBJECT-TYPE
			SYNTAX	INTEGER
			MAX-ACCESS	read-only
			STATUS	current
			::= { hmWanMbusFE 54 }

hmWanMbusFEValue18		OBJECT-TYPE
			SYNTAX	INTEGER
			MAX-ACCESS	read-only
			STATUS	current
			::= { hmWanMbusFE 55 }

hmWanMbusFEVIF19		OBJECT-TYPE
			SYNTAX	INTEGER
			MAX-ACCESS	read-only
			STATUS	current
			::= { hmWanMbusFE 56 }

hmWanMbusFEValue19		OBJECT-TYPE
			SYNTAX	INTEGER
			MAX-ACCESS	read-only
			STATUS	current
			::= { hmWanMbusFE 57 }

hmWanMbusFEVIF1A		OBJECT-TYPE
			SYNTAX	INTEGER
			MAX-ACCESS	read-only
			STATUS	current
			::= { hmWanMbusFE 58 }

hmWanMbusFEValue1A		OBJECT-TYPE
			SYNTAX	INTEGER
			MAX-ACCESS	read-only
			STATUS	current
			::= { hmWanMbusFE 59 }

hmWanMbusFEVIF1B		OBJECT-TYPE
			SYNTAX	INTEGER
			MAX-ACCESS	read-only
			STATUS	current
			::= { hmWanMbusFE 60 }

hmWanMbusFEValue1B		OBJECT-TYPE
			SYNTAX	INTEGER
			MAX-ACCESS	read-only
			STATUS	current
			::= { hmWanMbusFE 61 }

hmWanMbusFEVIF1C		OBJECT-TYPE
			SYNTAX	INTEGER
			MAX-ACCESS	read-only
			STATUS	current
			::= { hmWanMbusFE 62 }

hmWanMbusFEValue1C		OBJECT-TYPE
			SYNTAX	INTEGER
			MAX-ACCESS	read-only
			STATUS	current
			::= { hmWanMbusFE 63 }

hmWanMbusFEVIF1D		OBJECT-TYPE
			SYNTAX	INTEGER
			MAX-ACCESS	read-only
			STATUS	current
			::= { hmWanMbusFE 64 }

hmWanMbusFEValue1D		OBJECT-TYPE
			SYNTAX	INTEGER
			MAX-ACCESS	read-only
			STATUS	current
			::= { hmWanMbusFE 65 }

hmWanMbusFEVIF1E		OBJECT-TYPE
			SYNTAX	INTEGER
			MAX-ACCESS	read-only
			STATUS	current
			::= { hmWanMbusFE 66 }

hmWanMbusFEValue1E		OBJECT-TYPE
			SYNTAX	INTEGER
			MAX-ACCESS	read-only
			STATUS	current
			::= { hmWanMbusFE 67 }

hmWanMbusFEVIF1F		OBJECT-TYPE
			SYNTAX	INTEGER
			MAX-ACCESS	read-only
			STATUS	current
			::= { hmWanMbusFE 68 }

hmWanMbusFEValue1F		OBJECT-TYPE
			SYNTAX	INTEGER
			MAX-ACCESS	read-only
			STATUS	current
			::= { hmWanMbusFE 69 }

hmWanMbusFEVIF20		OBJECT-TYPE
			SYNTAX	INTEGER
			MAX-ACCESS	read-only
			STATUS	current
			::= { hmWanMbusFE 70 }

hmWanMbusFEValue20		OBJECT-TYPE
			SYNTAX	INTEGER
			MAX-ACCESS	read-only
			STATUS	current
			::= { hmWanMbusFE 71 }

hmWanMbusFEVIF21		OBJECT-TYPE
			SYNTAX	INTEGER
			MAX-ACCESS	read-only
			STATUS	current
			::= { hmWanMbusFE 72 }

hmWanMbusFEValue21		OBJECT-TYPE
			SYNTAX	INTEGER
			MAX-ACCESS	read-only
			STATUS	current
			::= { hmWanMbusFE 73 }

hmWanMbusFEVIF22		OBJECT-TYPE
			SYNTAX	INTEGER
			MAX-ACCESS	read-only
			STATUS	current
			::= { hmWanMbusFE 74 }

hmWanMbusFEValue22		OBJECT-TYPE
			SYNTAX	INTEGER
			MAX-ACCESS	read-only
			STATUS	current
			::= { hmWanMbusFE 75 }

hmWanMbusFEVIF23		OBJECT-TYPE
			SYNTAX	INTEGER
			MAX-ACCESS	read-only
			STATUS	current
			::= { hmWanMbusFE 76 }

hmWanMbusFEValue23		OBJECT-TYPE
			SYNTAX	INTEGER
			MAX-ACCESS	read-only
			STATUS	current
			::= { hmWanMbusFE 77 }

hmWanMbusFEVIF24		OBJECT-TYPE
			SYNTAX	INTEGER
			MAX-ACCESS	read-only
			STATUS	current
			::= { hmWanMbusFE 78 }

hmWanMbusFEValue24		OBJECT-TYPE
			SYNTAX	INTEGER
			MAX-ACCESS	read-only
			STATUS	current
			::= { hmWanMbusFE 79 }

hmWanMbusFEVIF25		OBJECT-TYPE
			SYNTAX	INTEGER
			MAX-ACCESS	read-only
			STATUS	current
			::= { hmWanMbusFE 80 }

hmWanMbusFEValue25		OBJECT-TYPE
			SYNTAX	INTEGER
			MAX-ACCESS	read-only
			STATUS	current
			::= { hmWanMbusFE 81 }

hmWanMbusFEVIF26		OBJECT-TYPE
			SYNTAX	INTEGER
			MAX-ACCESS	read-only
			STATUS	current
			::= { hmWanMbusFE 82 }

hmWanMbusFEValue26		OBJECT-TYPE
			SYNTAX	INTEGER
			MAX-ACCESS	read-only
			STATUS	current
			::= { hmWanMbusFE 83 }

hmWanMbusFEVIF27		OBJECT-TYPE
			SYNTAX	INTEGER
			MAX-ACCESS	read-only
			STATUS	current
			::= { hmWanMbusFE 84 }

hmWanMbusFEValue27		OBJECT-TYPE
			SYNTAX	INTEGER
			MAX-ACCESS	read-only
			STATUS	current
			::= { hmWanMbusFE 85 }

hmWanMbusFEVIF28		OBJECT-TYPE
			SYNTAX	INTEGER
			MAX-ACCESS	read-only
			STATUS	current
			::= { hmWanMbusFE 86 }

hmWanMbusFEValue28		OBJECT-TYPE
			SYNTAX	INTEGER
			MAX-ACCESS	read-only
			STATUS	current
			::= { hmWanMbusFE 87 }

hmWanMbusFEVIF29		OBJECT-TYPE
			SYNTAX	INTEGER
			MAX-ACCESS	read-only
			STATUS	current
			::= { hmWanMbusFE 88 }

hmWanMbusFEValue29		OBJECT-TYPE
			SYNTAX	INTEGER
			MAX-ACCESS	read-only
			STATUS	current
			::= { hmWanMbusFE 89 }

hmWanMbusFEVIF2A		OBJECT-TYPE
			SYNTAX	INTEGER
			MAX-ACCESS	read-only
			STATUS	current
			::= { hmWanMbusFE 90 }

hmWanMbusFEValue2A		OBJECT-TYPE
			SYNTAX	INTEGER
			MAX-ACCESS	read-only
			STATUS	current
			::= { hmWanMbusFE 91 }

hmWanMbusFEVIF2B		OBJECT-TYPE
			SYNTAX	INTEGER
			MAX-ACCESS	read-only
			STATUS	current
			::= { hmWanMbusFE 92 }

hmWanMbusFEValue2B		OBJECT-TYPE
			SYNTAX	INTEGER
			MAX-ACCESS	read-only
			STATUS	current
			::= { hmWanMbusFE 93 }

hmWanMbusFEVIF2C		OBJECT-TYPE
			SYNTAX	INTEGER
			MAX-ACCESS	read-only
			STATUS	current
			::= { hmWanMbusFE 94 }

hmWanMbusFEValue2C		OBJECT-TYPE
			SYNTAX	INTEGER
			MAX-ACCESS	read-only
			STATUS	current
			::= { hmWanMbusFE 95 }

hmWanMbusFEVIF2D		OBJECT-TYPE
			SYNTAX	INTEGER
			MAX-ACCESS	read-only
			STATUS	current
			::= { hmWanMbusFE 96 }

hmWanMbusFEValue2D		OBJECT-TYPE
			SYNTAX	INTEGER
			MAX-ACCESS	read-only
			STATUS	current
			::= { hmWanMbusFE 97 }

hmWanMbusFEVIF2E		OBJECT-TYPE
			SYNTAX	INTEGER
			MAX-ACCESS	read-only
			STATUS	current
			::= { hmWanMbusFE 98 }

hmWanMbusFEValue2E		OBJECT-TYPE
			SYNTAX	INTEGER
			MAX-ACCESS	read-only
			STATUS	current
			::= { hmWanMbusFE 99 }

hmWanMbusFEVIF2F		OBJECT-TYPE
			SYNTAX	INTEGER
			MAX-ACCESS	read-only
			STATUS	current
			::= { hmWanMbusFE 100 }

hmWanMbusFEValue2F		OBJECT-TYPE
			SYNTAX	INTEGER
			MAX-ACCESS	read-only
			STATUS	current
			::= { hmWanMbusFE 101 }


hmWanIo			OBJECT IDENTIFIER ::= { hmWanProtocolsMib 3 }

hmWanIoBin0      OBJECT-TYPE
        	SYNTAX	Gauge32
			MAX-ACCESS	read-only
			STATUS	current
			::= { hmWanIo 1 }

hmWanIoOut0      OBJECT-TYPE
			SYNTAX	Gauge32
			MAX-ACCESS	read-write
			STATUS	current
			::= { hmWanIo 2 }

hmWanIoBin1      OBJECT-TYPE
        	SYNTAX	Gauge32
			MAX-ACCESS	read-only
			STATUS	current
			::= { hmWanIo 3 }


hmWanIoOut1      OBJECT-TYPE
        		SYNTAX	Gauge32
			MAX-ACCESS	read-write
			STATUS	current
			::= { hmWanIo 4 }

END
