HMIT-SW-PORT-STORM-MIB DEFINITIONS ::= BEGIN

IMPORTS
		MODULE-IDENTITY, OBJECT-TYPE
                FROM SNMPv2-SMI
        NOTIFICATION-TYPE
        	FROM SNMPv2-SMI
        hmITSwitchTech
        	FROM HMIT-SMI
		hmITSwPortMIB
			FROM HMIT-SW-PORT-MGR-MIB;

hmITPortStorm MODULE-IDENTITY
				LAST-UPDATED "201001081700Z"
                ORGANIZATION
                    "Belden Singapore Pte Ltd."
                CONTACT-INFO
                    "Belden Singapore Pte Ltd."
				DESCRIPTION
					"Port Storm"
				REVISION "201001081700Z"
				DESCRIPTION
					"The initial revision of this mib module "
				::= {hmITSwPortMIB 7}

portStorm	NOTIFICATION-TYPE
    STATUS  current
    DESCRIPTION
        "Occur storm for port."
    ::= { hmITPortStorm 1 }

portStormShutdown	NOTIFICATION-TYPE
    STATUS  current
    DESCRIPTION
        "Shutdown port when occur storm."
    ::= { hmITPortStorm 2 }
END
