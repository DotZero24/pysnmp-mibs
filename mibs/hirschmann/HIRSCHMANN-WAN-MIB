HIRSCHMANN-WAN-MIB DEFINITIONS ::= BEGIN

--
-- *************************************************************
-- Hirschmann WAN MIB
-- *************************************************************
--

IMPORTS
    MODULE-IDENTITY, enterprises, Unsigned32
        FROM SNMPv2-SMI -- RFC 2578
    TEXTUAL-CONVENTION
        FROM SNMPv2-TC; -- RFC 2579

hmWanMib MODULE-IDENTITY
	LAST-UPDATED "201502130000Z" -- Februar 13, 2015
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Copyright (C) 2015. All Rights Reserved."
    REVISION     "201502130000Z" -- Februar 13, 2015
    DESCRIPTION
         "Initial version."
    ::= { hirschmann 40 }

hirschmann	    OBJECT IDENTIFIER ::= { enterprises 248 }
hmWanMgmt		OBJECT IDENTIFIER ::= { hmWanMib 1 }

END
