-- ***************************************************************************
-- HMIT-SMI.mib:  Enterprise Structure of Hirschmann IT Management Information

-- Copyright ⓒ 2019 Belden Singapore Pte Ltd. All rights reserved.
--
-- ***************************************************************************

HMIT-SMI DEFINITIONS ::= BEGIN

IMPORTS
	MODULE-IDENTITY,
	OBJECT-IDENTITY,
	enterprises
		FROM SNMPv2-SMI;

hirschmann	MODULE-IDENTITY
	LAST-UPDATED "201001081700Z"
	ORGANIZATION "Belden Singapore Pte Ltd."
	CONTACT-INFO
		"Belden Singapore Pte Ltd."
	DESCRIPTION
		"The Structure of Management Information for Hirschmann."
	REVISION "201001081700Z"
    DESCRIPTION
		"The initial revision of this mib module "
	::= { enterprises 248 }

hmVendor OBJECT-IDENTITY
	STATUS	current
	DESCRIPTION
		"Hirschmann Vendor"
	::= { hirschmann 100 }

hmITSwitch OBJECT-IDENTITY
	STATUS	current
	DESCRIPTION
		"Hirschmann IT SWITCH"
	::= { hmVendor 1 }

hmITProducts OBJECT-IDENTITY
	STATUS	current
	DESCRIPTION
		"products is the root OBJECT IDENTIFIER from which sysObjectID
		values are assigned."
	::= { hmITSwitch 1 }

hmITTrapObject	OBJECT-IDENTITY
	STATUS	current
	DESCRIPTION
		"main subtree for hirschmann Traps."
	::= { hmITSwitch 2 }

hmITMgmt OBJECT-IDENTITY
	STATUS	current
	DESCRIPTION
		"hmITMgmt is the main subtree for implemented MIB branch.
		Note that different type of products may have the same
		protocol implementation, so we put such content into here so
		that every types could utilize corresponding module."
	::= { hmITSwitch 3 }

hmITExperiment OBJECT-IDENTITY
	STATUS	current
	DESCRIPTION
		"Experiment provides a root object identifier from which
		experimental mibs may be temporarily based. MIBs are typicially
		based here if they fall in one of two categories:

		1) IETF work-in-process mibs which have not been assigned a
		   permanent object identifier by the IANA.
		2) work-in-process which has not been assigned a
		   permanent object identifier by the assigned number
		   authority, typicially because the mib is not ready for
		   deployment.

		NOTE:  support for mibs in the Experiment subtree will be
		erased when a permanent object identifier assignment is made."
	::= { hmITSwitch 4 }


hmITSecurity	OBJECT-IDENTITY
	STATUS	current
	DESCRIPTION
		"hmITSecurity is the main subtree for security product MIB branch."
	::= { hmITSwitch 5 }

--2007.10.22
hmITMgmt2        OBJECT-IDENTITY
	STATUS	current
	DESCRIPTION
		"hmITMgmt2 is the new subtree for implemented MIB branch."
	::= { hmITSwitch 6 }

hmITSystem      OBJECT-IDENTITY
	STATUS	current
	DESCRIPTION
		"hmITSystem is the subtree for system mib."
	::= { hmITMgmt2 1 }

hmITRouterTech    OBJECT-IDENTITY
	STATUS	current
	DESCRIPTION
		"hmITLayer2 is the subtree for Layer3 MIB."
	::= { hmITMgmt2 2 }

hmITSwitchTech      OBJECT-IDENTITY
	STATUS	current
	DESCRIPTION
		"hmITLayer3 is the subtree for Layer2 MIB."
	::= { hmITMgmt2 3 }

hmITVoipTech        OBJECT-IDENTITY
	STATUS	current
	DESCRIPTION
		"hmITVoip is the subtree for voip MIB."
	::= { hmITMgmt2 4 }

hmITSecurityTech    OBJECT-IDENTITY
	STATUS	current
	DESCRIPTION
		"hmITSec  is the subtree for security MIB"
	::= { hmITMgmt2 5 }

hmITApp        OBJECT-IDENTITY
	STATUS	current
	DESCRIPTION
		"hmITApp is the subtree for application MIB."
	::= { hmITMgmt2 6 }

hmITOtherSys        OBJECT-IDENTITY
	STATUS	current
	DESCRIPTION
		"hmITOtherSys is the subtree for third part MIB."
	::= { hmITMgmt2 7 }

END
