------------------------------------------------------------------------------
--
--  File         : HMIT-SW-PORT-MGR-MIB.mib
--  Description  :
--  Version      :
--  Copyright    : Copyright ⓒ 2019 Belden Singapore Pte Ltd., All rights reserved.
--
-- $Id:
--
------------------------------------------------------------------------------

------------------------------------------------------------------------------

HMIT-SW-PORT-MGR-MIB DEFINITIONS ::= BEGIN

IMPORTS
        MODULE-IDENTITY, OBJECT-TYPE, Integer32, Unsigned32, IpAddress, Counter64
                FROM SNMPv2-SMI
	    RowStatus, DisplayString, PhysAddress, MacAddress
                FROM SNMPv2-TC
        hmITSwitchTech
                FROM HMIT-SMI;

hmITSwPortMIB MODULE-IDENTITY
				LAST-UPDATED "201001081700Z"
                ORGANIZATION
                    "Belden Singapore Pte Ltd."
                CONTACT-INFO
                    "Belden Singapore Pte Ltd."
				DESCRIPTION
					"Port Module"
				REVISION "201001081700Z"
				DESCRIPTION
					"The initial revision of this mib module "
				::= {hmITSwitchTech 1}

hmITSwPortmgrMIB      OBJECT IDENTIFIER ::= {hmITSwPortMIB 13}

hmITPortmgrTable  OBJECT-TYPE
    SYNTAX  SEQUENCE OF HmITPortmgrEntry
    MAX-ACCESS  not-accessible
    STATUS  current
    DESCRIPTION
            "The configuration table of the ports on the switch."
    ::= {hmITSwPortmgrMIB 2}

hmITPortmgrEntry  OBJECT-TYPE
    SYNTAX  HmITPortmgrEntry
    MAX-ACCESS  not-accessible
    STATUS  current
    DESCRIPTION
            "The configuration information of the port on the switch."
    INDEX   { hmITPortId }
    ::= {hmITPortmgrTable 1}

HmITPortmgrEntry ::=
SEQUENCE {
    hmITPortId            INTEGER,
    hmITMgrLinkStatus     INTEGER,
    hmITDescription       DisplayString,
    hmITMgrDuplex         INTEGER,
    hmITMgrSpeed          INTEGER,
    hmITFlowControl       INTEGER,
    hmITMdix              INTEGER,
    hmITMtu               INTEGER,
    hmITLinkDelay         INTEGER,
    hmITLoopBack          INTEGER,
    hmITActualLinkStatus  INTEGER,
    hmITActualDuplex      INTEGER,
    hmITActualSpeed       INTEGER,
    hmITPhyType           INTEGER,
    hmITPhyMacAddress     MacAddress,
    hmITPortMgrPortAbility    Counter64,
    hmITPortMgrPortType   INTEGER,
    hmITPortMgrJumbo      INTEGER,
    hmITPortMgrMediumType INTEGER,
    hmITPeerDescription   DisplayString,
    hmITPortMgrRowStatus  RowStatus
}

hmITPortId    OBJECT-TYPE
    SYNTAX  INTEGER (1..2147483647)
    MAX-ACCESS  not-accessible
    STATUS  current
    DESCRIPTION
            "The index of the port."
    ::= {hmITPortmgrEntry 1}

hmITMgrLinkStatus OBJECT-TYPE
    SYNTAX  INTEGER {
    	noshutdown(1),
    	shutdown(2)
    }
    MAX-ACCESS  read-write
    STATUS  current
    DESCRIPTION
            "The managed link status of the port, 1 - no shutdwon(Enable),
            2 - shutdown(Disable)."
    ::= {hmITPortmgrEntry 2}

hmITDescription   OBJECT-TYPE
    SYNTAX  DisplayString (SIZE (0..240))
    MAX-ACCESS  read-write
    STATUS  current
    DESCRIPTION
            "The description of the port."
    ::= {hmITPortmgrEntry 3}

hmITMgrDuplex OBJECT-TYPE
    SYNTAX  INTEGER {
    	duplexauto(1),
    	duplexhalf(2),
    	duplexfull(3)
    }
    MAX-ACCESS  read-write
    STATUS  current
    DESCRIPTION
            "The managed duplex mode of the port, 1 - auto,
            2 - half, 3 - full"
    ::= {hmITPortmgrEntry 4}

hmITMgrSpeed  OBJECT-TYPE
    SYNTAX  INTEGER {
    	speedauto(1),
    	speed10M(2),
    	speed100M(3),
    	speed1000M(4),
    	speed10000M(5),
		speed40000M(6),
		speed100G(7),
    	speed25000M(8),
    	speed2500M(11),
    	speed13000M(12)
    }
    MAX-ACCESS  read-write
    STATUS  current
    DESCRIPTION
            "The managed speed of the port."
    ::= {hmITPortmgrEntry 5}

hmITFlowControl   OBJECT-TYPE
    SYNTAX  INTEGER {
        enable(1),
        disable(2)
    }
    MAX-ACCESS  read-write
    STATUS  current
    DESCRIPTION
            "The flow control of the port."
    ::= {hmITPortmgrEntry 6}

hmITMdix      OBJECT-TYPE
    SYNTAX  INTEGER {
        auto(1),
        normal(2),
        cross(3)
    }
    MAX-ACCESS  read-write
    STATUS  current
    DESCRIPTION
            "The mdix mode of the port."
    ::= {hmITPortmgrEntry 7}

hmITMtu       OBJECT-TYPE
    SYNTAX  INTEGER (64..12288)
    MAX-ACCESS  read-write
    STATUS  current
    DESCRIPTION
            "The MTU length of the port, its range from 64 to 12288."
    ::= {hmITPortmgrEntry 8}

hmITLinkDelay OBJECT-TYPE
    SYNTAX  INTEGER (0..10)
    MAX-ACCESS  read-write
    STATUS  current
    DESCRIPTION
            "The delay time of the actual link status of the port
            from be down to be reported, measured by the second. When value is 0,
            it means to be reported immediately. its available value is 0, and
            from 2 to 10."
    ::= {hmITPortmgrEntry 9}

hmITLoopBack  OBJECT-TYPE
    SYNTAX  INTEGER {
        disable(1),
        internal(2),
        external(3)
    }
    MAX-ACCESS  read-write
    STATUS  current
    DESCRIPTION
            "Loopback test on the port, don't save its configuration."
    ::= {hmITPortmgrEntry 10}

hmITActualLinkStatus  OBJECT-TYPE
    SYNTAX  INTEGER {
    	up(1),
    	down(2)
    }
    MAX-ACCESS  read-only
    STATUS  current
    DESCRIPTION
            "The actual link status of the port."
    ::= {hmITPortmgrEntry 11}

hmITActualDuplex  OBJECT-TYPE
    SYNTAX  INTEGER {
        duplexunknown(1),
        duplexhalf(2),
        duplexfull(3)
    }
    MAX-ACCESS  read-only
    STATUS  current
    DESCRIPTION
            "The actual duplex mode of the port."
    ::= {hmITPortmgrEntry 12}

hmITActualSpeed   OBJECT-TYPE
    SYNTAX  INTEGER {
    	speedauto(1),
    	speed10M(2),
    	speed100M(3),
    	speed1000M(4),
    	speed10000M(5),
		speed40000M(6),
		speed100G(7),
    	speed25000M(8),
    	speed2500M(11),
    	speed13000M(12)
    }
    MAX-ACCESS  read-only
    STATUS  current
    DESCRIPTION
            "The actual speed of the port, measured by Mbps"
    ::= {hmITPortmgrEntry 13}

hmITPhyType   OBJECT-TYPE
    SYNTAX  INTEGER {
    	copper(1),
    	fiber(2)
    }
    MAX-ACCESS  read-only
    STATUS  current
    DESCRIPTION
            "The physical type of the port, 1 - copper, 2 - fiber"
    ::= {hmITPortmgrEntry 14}

hmITPhyMacAddress OBJECT-TYPE
    SYNTAX  MacAddress
    MAX-ACCESS  read-only
    STATUS  current
    DESCRIPTION
            "The MAC address of the port."
    ::= {hmITPortmgrEntry 15}

hmITPortMgrPortAbility    OBJECT-TYPE
    SYNTAX  Counter64
    MAX-ACCESS  read-only
    STATUS  current
    DESCRIPTION
            "The physical ability of the port."
    ::= {hmITPortmgrEntry 16}

hmITPortMgrPortType   OBJECT-TYPE
    SYNTAX  INTEGER {
    	lan(1),
    	wan(2)
    }
    MAX-ACCESS  read-write
    STATUS  current
    DESCRIPTION
            "The port mode of the port."
    ::= {hmITPortmgrEntry 17}

hmITPortMgrJumbo  OBJECT-TYPE
    SYNTAX  INTEGER (1..10)
    MAX-ACCESS  read-write
    STATUS  current
    DESCRIPTION
            "The jumbo status of the port."
    ::= {hmITPortmgrEntry 18}

hmITPortMgrMediumType OBJECT-TYPE
    SYNTAX  INTEGER {
        auto(1),
    	copper(2),
    	fiber(3),
        fiber2copper(4)
    }
    MAX-ACCESS  read-write
    STATUS  current
    DESCRIPTION
            "The medium type of the port."
    ::= {hmITPortmgrEntry 19}

hmITPeerDescription   OBJECT-TYPE
    SYNTAX  DisplayString (SIZE (0..240))
    MAX-ACCESS  read-write
    STATUS  current
    DESCRIPTION
            "The peer description of the port."
    ::= {hmITPortmgrEntry 20}

hmITPortMgrRowStatus  OBJECT-TYPE
    SYNTAX  RowStatus
    MAX-ACCESS  read-create
    STATUS  current
    DESCRIPTION
            "No longer in use."
    ::= {hmITPortmgrEntry 21}

END
