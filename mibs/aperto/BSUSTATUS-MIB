BSUSTATUS-MIB DEFINITIONS ::= BEGIN

	IMPORTS
		OBJECT-TYPE, MODULE-IDENTITY, Integer32
			FROM SNMPv2-SMI
		DisplayString
			FROM SNMPv2-TC
		aniBsuWirelessPort
			FROM BSUWIRELESSIF-MIB
		bsu
			FROM ANIROOT-MIB;


aniBsuStatus  MODULE-IDENTITY
	LAST-UPDATED "0209251510Z"      -- Wed Sep 25 15:10:00 PDT 2002
	ORGANIZATION "Aperto Networks"
	CONTACT-INFO
	  "
	  Postal:  Aperto Networks Inc
		   1637 S Main Street
		   Milpitas, California 95035
	  Tel:	   +1 408 719 9977
	  "
	DESCRIPTION
	   "This group shows the Status Information for the BSU.

	    The aniBsuStatusRadioTable shows the information for
	    each radio that is connected to the BSU.
	   "
	::= { bsu 1 }

	-- the BSU Status group

aniBsuStatusBootState OBJECT-TYPE
	SYNTAX INTEGER {
			starting(1),
			dhcpc-req-sent(2),
			configf-req-sent(3),
			wait-for-tod(4),
			wait-for-wss(5),
			operational(6),
			standby(7)
	}
	MAX-ACCESS  read-only
	STATUS      current
	DESCRIPTION
	   "Shows the current state of the BSU.
	   "
	--DEFAULT next-function-async     std_next_async
	::= { aniBsuStatus 1 }

aniBsuStatusSysUpTime OBJECT-TYPE
	SYNTAX      DisplayString (SIZE (0..22))
	MAX-ACCESS  read-only
	STATUS      current
	DESCRIPTION
	   "Time for which the system has been up and running,
	    displayed as a string in 'days hours mins secs' format.
	   "
	--DEFAULT next-function-async     std_next_async
	::= { aniBsuStatus 2 }

aniBsuStatusNumPortsConf OBJECT-TYPE
	SYNTAX      INTEGER
	MAX-ACCESS  read-only
	STATUS      current
	DESCRIPTION
	   "The number of wireless ports configured.
	   "
	--DEFAULT next-function-async     std_next_async
	::= { aniBsuStatus 3 }

aniBsuStatusNumPortsPresent OBJECT-TYPE
	SYNTAX      INTEGER
	MAX-ACCESS  read-only
	STATUS      current
	DESCRIPTION
	   "The number of wireless ports actually available.
	   "
	--DEFAULT next-function-async     std_next_async
	::= { aniBsuStatus 4 }

aniBsuStatusSuCounts OBJECT-TYPE
	SYNTAX      INTEGER (1..6144)
	MAX-ACCESS  read-only
	STATUS      current
	DESCRIPTION
	   "The total SUs linked to the BSU.
	   "
	--DEFAULT next-function-async     std_next_async
	::= { aniBsuStatus 5 }

aniBsuStatusCellName OBJECT-TYPE
	SYNTAX      DisplayString (SIZE (0..31))
	MAX-ACCESS  read-only
	STATUS      current
	DESCRIPTION
	   "The name of the Cell this BSU belongs to.

	    When BSU is in point to point mode, this parameter is
	    not applicable and will display an empty string.
	    Similarly for PacketWave 750, this parameter is
	    not applicable and will display an empty string.
	   "
	--DEFAULT next-function-async     std_next_async
	::= { aniBsuStatus 6 }

aniBsuStatusCellRadius OBJECT-TYPE
	SYNTAX      INTEGER {
			radius10km(10000),
			radius20km(20000),
			radius30km(30000),
			radius40km(40000),
			radius50km(50000),
			radius60km(60000),
			radius70km(70000),
			radius80km(80000),
			radius90km(90000),
			radius100km(100000)
		}
	MAX-ACCESS  read-only
	STATUS      current
	DESCRIPTION
	   "The Cell Radius in km.

	    When BSU is in point to point mode, this object can be
	    referred to as link distance.
	   "
	--DEFAULT next-function-async     std_next_async
	::= { aniBsuStatus 7 }

aniBsuStatusSyncTimingRef  OBJECT-TYPE
	SYNTAX  INTEGER {
			internal (1),
			external (2),
			not-applicable(3)
		}
	MAX-ACCESS  read-only
	STATUS      current
	DESCRIPTION
	   "This flag shows whether timing reference is internal (1)
	    or external (2) for this BSU.

	    When BSU is running in point to point mode, this object is
	    not-applicable. Similarly for PacketWave 750, this object is
	    not-applicable.
	   "
	DEFVAL  { internal }
	--DEFAULT next-function-async     std_next_async
	::= { aniBsuStatus 8 }

aniBsuStatusRipFlag  OBJECT-TYPE
	SYNTAX  INTEGER {
			enable (1),
			disable (2)
		}
	MAX-ACCESS  read-only
	STATUS      current
	DESCRIPTION
	   "This flag shows whether RIP is enabled(1)
	    or disabled(2) for this BSU.

	    This is always disabled when BSU is in bridge mode.
	   "
	DEFVAL  { enable }
	--DEFAULT next-function-async     std_next_async
	::= { aniBsuStatus 9 }

aniBsuStatusMode  OBJECT-TYPE
	SYNTAX  INTEGER {
			router (1),
			bridge (2),
			vlan (3)
		}
	MAX-ACCESS  read-only
	STATUS      current
	DESCRIPTION
	   "The mode of the BSU.
	   "
	--DEFAULT next-function-async     std_next_async
	::= { aniBsuStatus 10 }


        -- BSU Radio Status Group

aniBsuStatusRadioTable OBJECT-TYPE
	SYNTAX      SEQUENCE OF AniBsuStatusRadioEntry
	MAX-ACCESS  not-accessible
	STATUS      current
	DESCRIPTION
	   "This table shows the status of each radio that is
	    connected to the BSU. The radio has to be operational
	    for information to be displayed. The radio status is
	    shown on a per wireless port basis.
	   "
	::= { aniBsuStatus 11 }

aniBsuStatusRadioEntry OBJECT-TYPE
	SYNTAX      AniBsuStatusRadioEntry
	MAX-ACCESS  not-accessible
	STATUS      current
	DESCRIPTION
	   "An entry with objects that provide information
	    for each radio connected to the BSU.
	   "
	INDEX { aniBsuWirelessPort }
	::= { aniBsuStatusRadioTable 1 }

AniBsuStatusRadioEntry ::= SEQUENCE {
    aniBsuStatusRadioSerialNum            DisplayString,
    aniBsuStatusRadioFrequency            DisplayString,
    aniBsuStatusRadioBand                 INTEGER,
    aniBsuStatusRadioEepromRev            DisplayString,
    aniBsuStatusRadioVRFlag               INTEGER,
    aniBsuStatusRadioSynth1Lock           INTEGER,
    aniBsuStatusRadioSynth2Lock           INTEGER,
    aniBsuStatusRadioTxGain               DisplayString,
    aniBsuStatusRadioRxGain               Integer32,
    aniBsuStatusRadioCurrentTxMaxPower    DisplayString,
    aniBsuStatusRadioIfCableLoss          DisplayString

	}

aniBsuStatusRadioSerialNum OBJECT-TYPE
	SYNTAX      DisplayString (SIZE (0..16))
	MAX-ACCESS  read-only
	STATUS      current
	DESCRIPTION
	   "The serial number of the radio board.
	   "
	::= { aniBsuStatusRadioEntry 1 }

aniBsuStatusRadioFrequency OBJECT-TYPE
	SYNTAX      DisplayString
	UNITS       "MHz"
	MAX-ACCESS  read-only
	STATUS      current
	DESCRIPTION
	   "The radio frequency in MHz.
	   "
	::= { aniBsuStatusRadioEntry 2 }

aniBsuStatusRadioBand OBJECT-TYPE
	SYNTAX	INTEGER {
			unii-5-3GHz(1),
			unii-5-8GHz(2),
			general-5-8GHz(3),
			ism-5-8GHz(10),
			mmds-2-6GHz(4),
			general-2-6GHz(5),
			general-3-5GHz(6),
			etsi-3-5GHz-50(7),
			etsi-3-5GHz-100(8),
			fdd-3-5GHz(11),
			general-5-3GHz(12)
		}
	MAX-ACCESS  read-only
	STATUS      current
	DESCRIPTION
	   "The radio frequency band.
	   "
	::= { aniBsuStatusRadioEntry 3 }

aniBsuStatusRadioEepromRev OBJECT-TYPE
	SYNTAX      DisplayString
	MAX-ACCESS  read-only
	STATUS      current
	DESCRIPTION
	   "The radio EEPROM content revision number.
	   "
	::= { aniBsuStatusRadioEntry 4 }

aniBsuStatusRadioVRFlag OBJECT-TYPE
	SYNTAX  INTEGER {
			operational (1),
			not-operational (2)
		}
	MAX-ACCESS  read-only
	STATUS      current
	DESCRIPTION
	   "The status of the voltage regulator.
	   "
	::= { aniBsuStatusRadioEntry 5 }

aniBsuStatusRadioSynth1Lock OBJECT-TYPE
	SYNTAX  INTEGER {
			not-locked (1),
			locked (2)
		}
	MAX-ACCESS  read-only
	STATUS      current
	DESCRIPTION
	   "The status of the radio synthesizer 1 lock.
	   "
	::= { aniBsuStatusRadioEntry 6 }

aniBsuStatusRadioSynth2Lock OBJECT-TYPE
	SYNTAX  INTEGER {
			not-locked (1),
			locked (2)
		}
	MAX-ACCESS  read-only
	STATUS      current
	DESCRIPTION
	   "The status of the radio synthesizer 1 lock.
	   "
	::= { aniBsuStatusRadioEntry 7 }

aniBsuStatusRadioTxGain OBJECT-TYPE
	SYNTAX      DisplayString
	UNITS       "dB"
	MAX-ACCESS  read-only
	STATUS      current
	DESCRIPTION
	   "The radio transmit gain in dB.
	   "
	::= { aniBsuStatusRadioEntry 8 }

aniBsuStatusRadioRxGain OBJECT-TYPE
	SYNTAX      Integer32 (30..45)
	UNITS       "dB"
	MAX-ACCESS  read-only
	STATUS      current
	DESCRIPTION
	   "The radio receive gain in dB.
	   "
	::= { aniBsuStatusRadioEntry 9 }

aniBsuStatusRadioCurrentTxMaxPower OBJECT-TYPE
	SYNTAX      DisplayString
	UNITS       "dBm"
	MAX-ACCESS  read-only
	STATUS      current
	DESCRIPTION
	   "The radio current transmit maxium power in dBm
	   "
	::= { aniBsuStatusRadioEntry 10 }

aniBsuStatusRadioIfCableLoss OBJECT-TYPE
	SYNTAX      DisplayString
	UNITS       "dB"
	MAX-ACCESS  read-only
	STATUS      current
	DESCRIPTION
	   "The calculated IF cable loss in dB
	   "
	::= { aniBsuStatusRadioEntry 11 }

END
