BSUSUSTATUS-MIB DEFINITIONS ::= BEGIN

	IMPORTS
		OBJECT-TYPE, MODULE-IDENTITY, Integer32
			FROM SNMPv2-SMI
		IpAddress
			FROM RFC1155-SMI
		MacAddress, DisplayString
			FROM SNMPv2-TC
		aniBsuWirelessPort
			FROM BSUWIRELESSIF-MIB
		aniBsuSuGroup
			FROM ANIROOT-MIB;

aniBsuSuStatus  MODULE-IDENTITY
	LAST-UPDATED "0105091130Z"      -- Wed May 9 11:30:00 PDT 2001
	ORGANIZATION "Aperto Networks"
	CONTACT-INFO
	  "
	  Postal:  Aperto Networks Inc
		   1637 S Main Street
		   Milpitas, California 95035
	  Tel:	   +1 408 719 9977
	  "
	DESCRIPTION
	   "This group allows the users of the BSU to access status
	    information about the SU.

	    It consists of 2 tables - The Upstream Link Status Table
	    and Downstream Link Status Table.
	   "
	::= { aniBsuSuGroup 3 }

aniBsuSuUSLinkStatusTable OBJECT-TYPE
	SYNTAX      SEQUENCE OF AniBsuSuUSLinkStatusEntry
	MAX-ACCESS  not-accessible
	STATUS      current
	DESCRIPTION
	   "This table accesses the upstream status attributes of
	    each SU connected to this BSU.
	   "
        ::= { aniBsuSuStatus 1 }

aniBsuSuUSLinkStatusEntry OBJECT-TYPE
	SYNTAX      AniBsuSuUSLinkStatusEntry
	MAX-ACCESS  not-accessible
	STATUS      current
	DESCRIPTION
	   "Upstream Status information for a single SU.
	    An entry in this table exists for each SU that is connected
	    to the BSU.
	   "
	INDEX { aniBsuWirelessPort, aniBsuSuStatusMacAddr }
	::= { aniBsuSuUSLinkStatusTable 1 }

AniBsuSuUSLinkStatusEntry ::= SEQUENCE {
	aniBsuSuStatusMacAddr      	MacAddress,
	aniBsuSuStatusIpAddr      	IpAddress,
	aniBsuSuStatusUSPolarization	INTEGER,
	aniBsuSuStatusUSModulation	INTEGER,
	aniBsuSuStatusUSFec		INTEGER,
	aniBsuSuStatusSuTxPowerAttn  	Integer32,
	aniBsuSuStatusUSRxPower			Integer32,
	aniBsuSuStatusSuTxPower			Integer32

	}

aniBsuSuStatusMacAddr  OBJECT-TYPE
	SYNTAX	MacAddress
	MAX-ACCESS  read-only
	STATUS      current
	DESCRIPTION
	   "The SU MAC Address.
	   "
	::= { aniBsuSuUSLinkStatusEntry 1 }

aniBsuSuStatusIpAddr  OBJECT-TYPE
	SYNTAX	IpAddress
	MAX-ACCESS  read-only
	STATUS      current
	DESCRIPTION
	   "The SU IP Address.
	   "
	::= { aniBsuSuUSLinkStatusEntry 2 }

aniBsuSuStatusUSPolarization  OBJECT-TYPE
	SYNTAX	INTEGER {
		horizontal(1),
		vertical(2)
	}
	MAX-ACCESS  read-only
	STATUS      current
	DESCRIPTION
	   "The upstream Polarization.
	    This field is used by SU to adjust the polarization
	    selection when transmitting a burst to the BSU.
	    Each SU has a single antenna which can be polarized
	    either horizontally(1) or vertically(2).
	   "
	::= { aniBsuSuUSLinkStatusEntry 3 }


aniBsuSuStatusUSModulation  OBJECT-TYPE
	SYNTAX	INTEGER {
		qpsk(1),
		qam16(2)
	}
	MAX-ACCESS  read-only
	STATUS      current
	DESCRIPTION
	   "The current upstream Modulation for this SU.
	   "
	::= { aniBsuSuUSLinkStatusEntry 4 }

aniBsuSuStatusUSFec  OBJECT-TYPE
	SYNTAX	INTEGER {
		low(1),
		high(2)
	}
	MAX-ACCESS  read-only
	STATUS      current
	DESCRIPTION
	   "The current upstream FEC method for this SU.
	   "
	::= { aniBsuSuUSLinkStatusEntry 5 }

aniBsuSuStatusSuTxPowerAttn    OBJECT-TYPE
	SYNTAX      Integer32 (4..62)
	UNITS       "dB"
	MAX-ACCESS  read-only
	STATUS      current
	DESCRIPTION
	   "The SU Tx Power Attenuation.
	   "
	::= { aniBsuSuUSLinkStatusEntry 6 }

aniBsuSuStatusUSRxPower  OBJECT-TYPE
	SYNTAX      Integer32
	UNITS       "dBm"
	MAX-ACCESS  read-only
	STATUS      current
	DESCRIPTION
	   "The Upstream Receive Power. The value -130 is considered invalid.
	   "
	::= { aniBsuSuUSLinkStatusEntry 7 }

aniBsuSuStatusSuTxPower  OBJECT-TYPE
	SYNTAX      Integer32
	UNITS       "dBm"
	MAX-ACCESS  read-only
	STATUS      current
	DESCRIPTION
	   "The Upstream SU Tx Power. The value -130 is considered invalid.
	   "
	::= { aniBsuSuUSLinkStatusEntry 8 }



aniBsuSuDSLinkStatusTable OBJECT-TYPE
	SYNTAX      SEQUENCE OF AniBsuSuDSLinkStatusEntry
	MAX-ACCESS  not-accessible
	STATUS      current
	DESCRIPTION
	   "This table accesses the downstream status attributes of
	    each SU connected to this BSU.
	   "
        ::= { aniBsuSuStatus 2 }

aniBsuSuDSLinkStatusEntry OBJECT-TYPE
	SYNTAX      AniBsuSuDSLinkStatusEntry
	MAX-ACCESS  not-accessible
	STATUS      current
	DESCRIPTION
	   "Downstream Status information for a single SU.
	    An entry in this table exists for each SU that is connected
	    to the BSU.
	   "
	INDEX { aniBsuWirelessPort, aniBsuSuStatusMacAddr }
	::= { aniBsuSuDSLinkStatusTable 1 }

AniBsuSuDSLinkStatusEntry ::= SEQUENCE {
	aniBsuSuStatusDSPolarization	INTEGER,
	aniBsuSuStatusDSModulation	INTEGER,
	aniBsuSuStatusDSFec		INTEGER,
	aniBsuSuStatusDSRxPower		DisplayString,
	aniBsuSuStatusBsuTxPower	Integer32

	}

aniBsuSuStatusDSPolarization  OBJECT-TYPE
	SYNTAX	INTEGER {
		horizontal(1),
		vertical(2)
	}
	MAX-ACCESS  read-only
	STATUS      current
	DESCRIPTION
	   "The downstream Polarization.
	    This field is used by BSU to adjust the polarization
	    selection when transmitting a burst to the SU.
	    Each SU has a single antenna which can be polarized
	    either horizontally(1) or vertically(2).
	   "
	::= { aniBsuSuDSLinkStatusEntry 1 }



aniBsuSuStatusDSModulation  OBJECT-TYPE
	SYNTAX	INTEGER {
		qpsk(1),
		qam16(2)
	}
	MAX-ACCESS  read-only
	STATUS      current
	DESCRIPTION
	   "The current downstream Modulation for this SU.
	   "
	::= { aniBsuSuDSLinkStatusEntry 2 }

aniBsuSuStatusDSFec  OBJECT-TYPE
	SYNTAX	INTEGER {
		low(1),
		high(2)
	}
	MAX-ACCESS  read-only
	STATUS      current
	DESCRIPTION
	   "The current downstream FEC method for this SU.
	   "
	::= { aniBsuSuDSLinkStatusEntry 3 }

aniBsuSuStatusDSRxPower  OBJECT-TYPE
	SYNTAX      DisplayString
	MAX-ACCESS  read-only
	STATUS      current
	DESCRIPTION
	   "The Downstream Receive Power in dBm. It consists of 2
	    values, one for vertical polarization and one for
	    horizontal polarization.
	    It is displayed as 'vertical,horizontal'
	    When nothing is being received, a value NA is displayed.
	    Eg. for vertical = -20 and horizontal = NA, the agent
	    will display '-20,NA'.
	   "
	::= { aniBsuSuDSLinkStatusEntry 5 }

aniBsuSuStatusBsuTxPower  OBJECT-TYPE
	SYNTAX      Integer32
	UNITS       "dBm"
	MAX-ACCESS  read-only
	STATUS      current
	DESCRIPTION
	   "The BSU Tx Power for a particular SU.
	   "
	::= { aniBsuSuDSLinkStatusEntry 6 }



aniBsuSuLinkStatusTable OBJECT-TYPE
	SYNTAX      SEQUENCE OF AniBsuSuLinkStatusEntry
	MAX-ACCESS  not-accessible
	STATUS      current
	DESCRIPTION
	   "This table accesses the other link status attributes of
	    each SU connected to this BSU.
	   "
        ::= { aniBsuSuStatus 3 }

aniBsuSuLinkStatusEntry OBJECT-TYPE
	SYNTAX      AniBsuSuLinkStatusEntry
	MAX-ACCESS  not-accessible
	STATUS      current
	DESCRIPTION
	   "Link Status information for a single SU.
	    An entry in this table exists for each SU that is connected
	    to the BSU.
	   "
	INDEX { aniBsuWirelessPort, aniBsuSuStatusMacAddr }
	::= { aniBsuSuLinkStatusTable 1 }

AniBsuSuLinkStatusEntry ::= SEQUENCE {
	aniBsuSuStatusIpAddress      	IpAddress,
	aniBsuSuStatusPropagationDelay	Integer32,
	aniBsuSuStatusDistance		DisplayString,
	aniBsuSuStatusLinkType		DisplayString,
	aniBsuSuStatusPathLossExponent	DisplayString
	}

aniBsuSuStatusIpAddress  OBJECT-TYPE
	SYNTAX	IpAddress
	MAX-ACCESS  read-only
	STATUS      current
	DESCRIPTION
	   "The SU IP Address.
	   "
	::= { aniBsuSuLinkStatusEntry 1 }

aniBsuSuStatusPropagationDelay  OBJECT-TYPE
	SYNTAX	Integer32
	MAX-ACCESS  read-only
	STATUS      current
	DESCRIPTION
	   "The time taken to transmit a packet from BSU to SU
	    (or vice versa) in microseconds.
	   "
	   ::= { aniBsuSuLinkStatusEntry 2 }

aniBsuSuStatusDistance  OBJECT-TYPE
	SYNTAX	DisplayString
	MAX-ACCESS  read-only
	STATUS      current
	DESCRIPTION
	   "The distance in meters between the BSU and SU.
	   "
	   ::= { aniBsuSuLinkStatusEntry 3 }

aniBsuSuStatusLinkType  OBJECT-TYPE
	SYNTAX      DisplayString
	MAX-ACCESS  read-only
	STATUS      current
	DESCRIPTION
	   "The link type for a particular SU.
	   "
	::= { aniBsuSuLinkStatusEntry 4 }

aniBsuSuStatusPathLossExponent  OBJECT-TYPE
	SYNTAX	DisplayString
	MAX-ACCESS  read-only
	STATUS      current
	DESCRIPTION
	   "The path loss exponent from BSU to SU
	   "
	   ::= { aniBsuSuLinkStatusEntry 5 }

	END
