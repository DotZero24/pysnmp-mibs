BSUCLK-MIB DEFINITIONS ::= BEGIN

	IMPORTS
		OBJECT-TYPE, MODULE-IDENTITY
			FROM SNMPv2-SMI
		DisplayString
			FROM SNMPv2-TC
		bsu
			FROM ANIROOT-MIB;

   aniBsuClock  MODULE-IDENTITY
	LAST-UPDATED "0105091130Z"      -- Wed May 9 11:30:00 PDT 2001
	ORGANIZATION "Aperto Networks"
	CONTACT-INFO
	  "
	  Postal:  Aperto Networks Inc
		   1637 S Main Street
		   Milpitas, California 95035
	  Tel:	   +1 408 719 9977
	  "
	DESCRIPTION
	"This module is used to configure the clock time on the BSU. BSUs
	 need to obtain and set their current clock time at boot up.
	 Sus will communicate with the BSU during their own boot up
	 and set their own clock time to that of BSU.
	 Time at the BSU can be set either through SNTP or manually.
	 It is recommended to use SNTP to obtain time.
	"
	::= { bsu 4 }

aniBsuClkSntpTimeZone OBJECT-TYPE
	SYNTAX      DisplayString (SIZE(0..6))
	MAX-ACCESS  read-write
	STATUS      current
	DESCRIPTION
	   "This is used to set the appropriate Time Zone offset from GMT.
        The format of data should be +Hour:Min or -Hour:Min.
		The valid Hour should be between -13 to +14
		The valid Min should be 00,15,30 or 45
		For example: +12:00 or +12:30 or -3:45
		"
	--DEFAULT next-function-async     std_next_async
	::= { aniBsuClock 1 }

aniBsuClkSntpDstEnable OBJECT-TYPE
	SYNTAX      INTEGER {
				 enable(1),
				 disable(2)
				 }
	MAX-ACCESS  read-write
	STATUS      current
	DESCRIPTION
	   "This shows whether Daylight Saving is enabled or not.
	    It gives user the option to incorporate Daylight Saving Time
	    in the configuration.
	   "
	DEFVAL { disable }
	--DEFAULT next-function-async     std_next_async
	::= { aniBsuClock 2 }

aniBsuClkSntpDstStart OBJECT-TYPE
	SYNTAX      DisplayString (SIZE(0..6))
	MAX-ACCESS  read-write
	STATUS      current
	DESCRIPTION
	   "Used to specify the start of Daylight Saving Time which should be
	    entered in the 'mmddhh' format where m - month, d - day and h - hour.
	    Can and must be set only if aniBsuClkSntpDstEnable is enabled.
	   "
	--DEFAULT next-function-async     std_next_async
	::= { aniBsuClock 3 }

aniBsuClkSntpDstEnd OBJECT-TYPE
	SYNTAX      DisplayString (SIZE(0..6))
	MAX-ACCESS  read-write
	STATUS      current
	DESCRIPTION
	   "Used to specify the end of Daylight Saving Time which should be
	    entered in the 'mmddhh' format where m - month, d - day and h - hour.
	    Can and must be set only if aniBsuClkSntpDstEnable is enabled.
	   "
	--DEFAULT next-function-async     std_next_async
	::= { aniBsuClock 4 }

aniBsuClkSntpEnable OBJECT-TYPE
	SYNTAX      INTEGER {
			 enable(1),
			 disable(2)
		 }
	MAX-ACCESS  read-write
	STATUS      current
	DESCRIPTION
	   "This flag is used to enable(1) or disable(2) SNTP.
	    It is recommended to use SNTP rather than manually setting the time
	    to avoid errors in clock times simply due to manual entry across
	    various BSUs.
	   "
	DEFVAL { enable }
	--DEFAULT next-function-async     std_next_async
	::= { aniBsuClock 5 }

aniBsuClkManualTime OBJECT-TYPE
	SYNTAX      DisplayString (SIZE(0..19))
	MAX-ACCESS  read-write
        STATUS      current
	DESCRIPTION
	   "Used to specify the local clock time manually. It should be
	    entered in the 'mm/dd/yyyy hh:mm:ss' format that is,
	 		month/day/year hour:minute:second.
	    When the user sends a set request on this parameter, the
	    aniBsuClkSntpEnable value is automatically set to disable(2), to set
	    this manual time entry on BSU.
	   "
	--DEFAULT next-function-async     std_next_async
	::= { aniBsuClock 6 }

aniBsuClkCurrentTime OBJECT-TYPE
	SYNTAX      DisplayString (SIZE (0..17))
	MAX-ACCESS  read-only
	STATUS      current
	DESCRIPTION
	   "The Current Time in 'mm/dd/yy hh:mm:ss' format, that is,
				month/day/year hour:minute:second.
	   "
	--DEFAULT next-function-async     std_next_async
	::= { aniBsuClock 7 }

		END
