ANIROOT-MIB DEFINITIONS ::= BEGIN

		IMPORTS
			private
		  		FROM RFC1155-SMI;

          --  ANI MIB Tree structure

		 enterprises   OBJECT IDENTIFIER ::= { private 1 }
		 ani           OBJECT IDENTIFIER ::= { enterprises 4325 }

		 topology      OBJECT IDENTIFIER ::= { ani 1 }
		 device        OBJECT IDENTIFIER ::= { ani 2 }
		 bsu           OBJECT IDENTIFIER ::= { ani 3 }
		 su            OBJECT IDENTIFIER ::= { ani 4 }

		 aniDevBase	 	 OBJECT IDENTIFIER ::= { device 1 }
		 aniDevSoftware	 	 OBJECT IDENTIFIER ::= { device 2 }
		 aniDevHardware	 	 OBJECT IDENTIFIER ::= { device 3 }
		 aniDevControl	 	 OBJECT IDENTIFIER ::= { device 4 }
		 aniDevServer	 	 OBJECT IDENTIFIER ::= { device 5 }
		 aniDevEvent	 	 OBJECT IDENTIFIER ::= { device 6 }
		 aniDevNetworkManager 	 OBJECT IDENTIFIER ::= { device 7 }
		 aniDevFilter	 	 OBJECT IDENTIFIER ::= { device 8 }
		 aniDevRoute	 	 OBJECT IDENTIFIER ::= { device 9 }
		 aniDevTrap	 	 OBJECT IDENTIFIER ::= { device 10 }
		 aniDevEthernet	 	 OBJECT IDENTIFIER ::= { device 11 }

		 aniBsuStatus		OBJECT IDENTIFIER ::= { bsu 1 }
		 aniBsuWirelessIf	OBJECT IDENTIFIER ::= { bsu 2 }
		 aniBsuStatistics   	OBJECT IDENTIFIER ::= { bsu 3 }
		 aniBsuClock   	   	OBJECT IDENTIFIER ::= { bsu 4 }
		 aniBsuBridge	    OBJECT IDENTIFIER ::= { bsu 5 }
		 aniBsuMultSubnets	OBJECT IDENTIFIER ::= { bsu 6 }
		 aniBsuSuGroup		OBJECT IDENTIFIER ::= { bsu 7 }
		 	aniBsuSuInventory    	OBJECT IDENTIFIER ::= { aniBsuSuGroup 1 }
		 	aniBsuSuBase    	OBJECT IDENTIFIER ::= { aniBsuSuGroup 2 }
		 	aniBsuSuStatus    	OBJECT IDENTIFIER ::= { aniBsuSuGroup 3 }
		 	aniBsuSuStatistics    	OBJECT IDENTIFIER ::= { aniBsuSuGroup 4 }
		 aniBsuParam		OBJECT IDENTIFIER ::= { bsu 8 }
		 aniBsuVlan		OBJECT IDENTIFIER ::= { bsu 11 }

 		 aniSuBase	  	OBJECT IDENTIFIER ::= { su 1 }
 		 aniSuStatus	  	OBJECT IDENTIFIER ::= { su 2 }
 		 aniSuStatistics 	OBJECT IDENTIFIER ::= { su 3 }
 		 aniSuClassifier   	OBJECT IDENTIFIER ::= { su 4 }
 		 aniSuServiceFlow  	OBJECT IDENTIFIER ::= { su 5 }
 		 aniSuNat	 	OBJECT IDENTIFIER ::= { su 6 }
 		 aniSuDhcp	 	OBJECT IDENTIFIER ::= { su 7 }
 		-- aniSuLinkAdaptation 	OBJECT IDENTIFIER ::= { su 8 } removed
		-- aniSuAntenna		OBJECT IDENTIFIER ::= { su 9 } removed
		 aniSuPppoe		OBJECT IDENTIFIER ::= { su 10 }
		 aniSuPpp		OBJECT IDENTIFIER ::= { su 11 }
		 aniSuVlan		OBJECT IDENTIFIER ::= { su 12 }
		 aniSuWireless		OBJECT IDENTIFIER ::= { su 13 }

END
