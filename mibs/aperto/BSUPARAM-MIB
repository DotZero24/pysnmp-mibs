BSUPARAM-MIB DEFINITIONS ::= BEGIN

	IMPORTS
		OBJECT-TYPE, MODULE-IDENTITY
			FROM SNMPv2-SMI
		bsu
			FROM ANIROOT-MIB;


aniBsuParam  MODULE-IDENTITY
	LAST-UPDATED "0111121130Z"      -- Wed Nov 12 11:30:00 PDT 2001
	ORGANIZATION "Aperto Networks"
	CONTACT-INFO
	  "
	  Postal:  Aperto Networks Inc
		   1637 S Main Street
		   Milpitas, California 95035
	  Tel:	   +1 408 719 9977
	  "
	DESCRIPTION
	   "This group contains other configurable parameters for the BSU.
	   "
	::= { bsu 8 }

	-- the BSU Param group

aniBsuDhcpParamSource  OBJECT-TYPE
	SYNTAX  INTEGER {
			local (1),
			server (2)
		}
	MAX-ACCESS  read-only
	STATUS      current
	DESCRIPTION
	   "This flag indicated the source of DHCP boot
	    parameters for the BSU.
	    This field is stored in the nvram and is updated
	    using the CLI.
	   "
	DEFVAL  { server }
	--DEFAULT next-function-async     std_next_async
	::= { aniBsuParam 1 }

END
