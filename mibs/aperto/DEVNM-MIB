DEVNM-MIB DEFINITIONS ::= BEGIN

	IMPORTS
		IpAddress
			FROM RFC1155-SMI
		OBJECT-TYPE, MODULE-IDENTITY
			FROM SNMPv2-SMI
		DisplayString
			FROM SNMPv2-TC
		device
			FROM ANIROOT-MIB;


   aniDevNetworkManager  MODULE-IDENTITY
	LAST-UPDATED "0105091130Z"      -- Wed May 9 11:30:00 PDT 2001
	ORGANIZATION "Aperto Networks"
	CONTACT-INFO
	  "
	  Postal:  Aperto Networks Inc
		   1637 S Main Street
		   Milpitas, California 95035
	  Tel:	   +1 408 719 9977
	  "
	DESCRIPTION
	"The aniDevNetworkMgrAccessTable provides one level of security
	 for access to the device by network management stations.
	 Access is also constrained by community strings.

	 Currently, creation and deletion of rows to this table through
	 SNMP Agent is not allowed.
	"
	::= { device 7 }

aniDevNumManagingHosts OBJECT-TYPE
	SYNTAX      INTEGER (0..2)
	MAX-ACCESS  read-only
	STATUS      current
	DESCRIPTION
	   "This object gives the number of Managing Hosts configured.
	   "
	--DEFAULT next-function-async     std_next_async
	::= { aniDevNetworkManager 1 }

aniDevNetworkMgrAccessTable OBJECT-TYPE
	SYNTAX      SEQUENCE OF AniDevNetworkMgrAccessEntry
	MAX-ACCESS  not-accessible
	STATUS      current
	DESCRIPTION
	   "This table controls access to SNMP objects by network
	    management stations. If the table is empty, access
	    to SNMP objects is unrestricted.
	   "
	::= { aniDevNetworkManager 2 }

aniDevNetworkMgrAccessEntry OBJECT-TYPE
	SYNTAX      AniDevNetworkMgrAccessEntry
	MAX-ACCESS  not-accessible
	STATUS      current
	DESCRIPTION
	   "Controls access to SNMP objects by a particular network
	    management station. For each entry in this table, the
	    contents are not readable unless the management station
	    has read-write permission.
	   "
	INDEX { aniDevNMAccessIndex  }
	::= {  aniDevNetworkMgrAccessTable 1 }

AniDevNetworkMgrAccessEntry ::= SEQUENCE {
	aniDevNMAccessIndex		INTEGER,
	aniDevNMAccessIp		IpAddress,
	aniDevNMReadAccessCommunity	DisplayString,
	aniDevNMWriteAccessCommunity	DisplayString,
	aniDevNMAccessControl		INTEGER
	}

aniDevNMAccessIndex OBJECT-TYPE
	SYNTAX      INTEGER (1..2)
	MAX-ACCESS  not-accessible
	STATUS      current
	DESCRIPTION
	   "Index used to order the table entries.
	   "
	::= { aniDevNetworkMgrAccessEntry 1 }

aniDevNMAccessIp OBJECT-TYPE
	SYNTAX      IpAddress
	MAX-ACCESS  read-write
	STATUS      current
	DESCRIPTION
	   "The IP address of the network management station.
	    The address 0.0.0.0 is defined to mean any NMS.
	    If traps are enabled for this entry, then the
	    value must be the address of a specific device.
	   "
	::= { aniDevNetworkMgrAccessEntry 2 }

aniDevNMReadAccessCommunity OBJECT-TYPE
	SYNTAX      DisplayString (SIZE(0..31))
	MAX-ACCESS  read-write
	STATUS      current
	DESCRIPTION
	   "The Read access community string to be matched for
	    access by this entry.
	   "
	DEFVAL { "public" }
	::= { aniDevNetworkMgrAccessEntry 3 }

aniDevNMWriteAccessCommunity OBJECT-TYPE
	SYNTAX      DisplayString (SIZE(0..31))
	MAX-ACCESS  read-write
	STATUS      current
	DESCRIPTION
	   "The Write access community string to be matched for
	    access by this entry.
	   "
	DEFVAL { "private" }
	::= { aniDevNetworkMgrAccessEntry 4 }

aniDevNMAccessControl OBJECT-TYPE
	SYNTAX	INTEGER {
			read(1),
			readWrite(2),
			roWithTraps(3),
			rwWithTraps(4),
			trapsOnly(5)
	}
	MAX-ACCESS  read-write
	STATUS      current
	DESCRIPTION
	   "Specifies the managing host access right to
	    this device.
	   "
	DEFVAL { readWrite }
	::= { aniDevNetworkMgrAccessEntry 5 }


	END
