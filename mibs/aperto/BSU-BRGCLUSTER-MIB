BSU-BRGCLUSTER-MIB DEFINITIONS ::= BEGIN

	IMPORTS
		OBJECT-TYPE, MODULE-IDENTITY
			FROM SNMPv2-SMI
		DisplayString
			FROM SNMPv2-TC
		bsu
			FROM ANIROOT-MIB;

aniBsuBridge  MODULE-IDENTITY
	LAST-UPDATED "0209251530Z"      -- Wed Sep 25 15:30:00 PDT 2002
	ORGANIZATION "Aperto Networks"
	CONTACT-INFO
	  "
	  Postal:  Aperto Networks Inc
		   1637 S Main Street
		   Milpitas, California 95035
	  Tel:	   +1 408 719 9977
	  "
	DESCRIPTION
	   "This group allows Configuration/Viewing of Bridging and
	    Clustering parameters for BSU. Clusters can be added and
	    deleted using Configuration Manager and viewed using SNMP.

	    When BSU is running in point to point mode, this group is
	    not applicable. Also for PacketWave 750 this group
	    is not applicable.
	   "
	::= { bsu 5 }

aniBsuSuBridgeEnable OBJECT-TYPE
        SYNTAX  INTEGER {
		 	enable(1),
		 	disable(2),
			not-applicable(3)
		 }
        MAX-ACCESS  read-only
        STATUS      current
        DESCRIPTION
	   "This parameter is used to enable/disable SU to SU bridging on BSU
	    wireless ports.

	    When BSU is running in point to point mode, this object is
	    not-applicable. Also for PacketWave 750, this group
	    is not-applicable.
	   "
	--DEFAULT next-function-async     std_next_async
        ::= { aniBsuBridge 1 }



END
