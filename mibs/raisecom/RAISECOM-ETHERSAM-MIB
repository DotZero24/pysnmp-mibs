--MibName=rcEtherSam
-- *****************************************************************
-- RAISECOM-ETHERSAM-MIB.mib
--
-- 20120810, yangzhonghong
--
-- Copyright(c) 2003-2005 by RAISECOM TECH, Ltd.
-- All rights reserved.
--03, 20130514, yangzh, add objects about rfc2544 test[REAP1.2]
--02, 20130425, yangzh,chang the max value of fd/fdv to 1000000us[1s]
--01, 20130313, yangzh,chang the max value of node rcEtherSamFlowFrameSize to 12288
-- *****************************************************************
RAISECOM-ETHERSAM-MIB DEFINITIONS ::= BEGIN
IMPORTS
    Integer32, Counter64,
    Unsigned32,IpAddress          FROM SNMPv2-SMI    -- [RFC2578]
	InetAddressType, InetAddress  FROM INET-ADDRESS-MIB
    RowStatus,MacAddress          FROM SNMPv2-TC     -- [RFC2579]
    iscomSwitch                   FROM RAISECOM-BASE-MIB
    EnableVar                     FROM SWITCH-TC
    ;
rcEtherSam  MODULE-IDENTITY
    LAST-UPDATED   "201209100000Z"
    ORGANIZATION   "Raisecom, Inc."
    CONTACT-INFO
                "       Raise Systems

                Postal: Beijing,
                        China

                   Tel: 86-010-82884499

                E-mail: yangzhonghong@raisecom.com"
    DESCRIPTION
        "This MIB module defines objects to Y.1564 "
        REVISION   "201209100000Z"
        DESCRIPTION
            "The initial revision of this MIB."
        ::={ iscomSwitch 74 }

--rcEtherSam
--rcEtherSamGlobalGroup
--rcEtherSamTestGroup
--rcEtherSamTestTrapGroup
rcEtherSamGlobalGroup                   OBJECT IDENTIFIER ::= { rcEtherSam 1 }
rcEtherSamTestGroup                   OBJECT IDENTIFIER ::= { rcEtherSam 2 }
rcEtherSamTestTrapGroup                   OBJECT IDENTIFIER ::= { rcEtherSam 3 }


-- rcEtherSamGlobalGroup Definitions
--rcEtherSamServiceList
--rcEtherSamServiceTestType
--rcEtherSamServiceTestOperate
--rcEtherSamPerformanceDuration
--rcEtherSamTestElapsedTime
--rcEtherSamServiceTestResult

rcEtherSamServiceList        OBJECT-TYPE
	SYNTAX      INTEGER
    MAX-ACCESS  read-write
    STATUS      current
    DESCRIPTION
            "Service List of EtherSam"
    ::= { rcEtherSamGlobalGroup 1 }

rcEtherSamServiceTestType        OBJECT-TYPE
	SYNTAX      INTEGER{
	            configuration (1),
                performance   (2),
                both          (3),
                rfc2544       (4),
                performance-inservice(5)
                }
    MAX-ACCESS  read-write
    STATUS      current
    DESCRIPTION
            "Service Test Type of EtherSam.'both' means configuration test and performance test."
    ::= { rcEtherSamGlobalGroup 2 }

rcEtherSamServiceTestOperate        OBJECT-TYPE
	SYNTAX      INTEGER{
	            start    (1),
	            stop     (2),
	            testing  (3),
	            idle     (4)
	            }
    MAX-ACCESS  read-write
    STATUS      current
    DESCRIPTION
            "Service test operation status."
    ::= { rcEtherSamGlobalGroup 3 }

rcEtherSamPerformanceDuration        OBJECT-TYPE
	SYNTAX      INTEGER(0|5..1440)
    MAX-ACCESS  read-write
    STATUS      current
    DESCRIPTION
            "EtherSam Performance Test Duration(in Min),'0' means testing untill doing stop operation."
    ::= { rcEtherSamGlobalGroup 4 }

rcEtherSamTestElapsedTime        OBJECT-TYPE
	SYNTAX      INTEGER(0..172800)
    MAX-ACCESS  read-only
    STATUS      current
    DESCRIPTION
            "The object specific the time that the test elapsed EtherSam Performance Test Duration."
    ::= { rcEtherSamGlobalGroup 5 }

rcEtherSamServiceTestResult        OBJECT-TYPE
	SYNTAX      INTEGER{
	            pass   (1),
	            fail   (2)
	            }
    MAX-ACCESS  read-only
    STATUS      current
    DESCRIPTION
            "Result of all the etherSam service test."
    ::= { rcEtherSamGlobalGroup 6 }

-- rcEtherSamTestGroup Definitions
--rcFlowProfileTable
--rcEtherSamServiceTable
--rcEtherSamCfgResultTable
--rcEtherSamPerformanceResultTable
--rcEtherSamStatisticTable

-- rcFlowProfileTable

rcEtherSamFlowTable OBJECT-TYPE
    SYNTAX      SEQUENCE OF RcEtherSamFlowEntry
    MAX-ACCESS  not-accessible
    STATUS      current
    DESCRIPTION
        "test flow profile table"
    ::= { rcEtherSamTestGroup 1 }

rcEtherSamFlowEntry   OBJECT-TYPE
    SYNTAX      RcEtherSamFlowEntry
    MAX-ACCESS  not-accessible
    STATUS      current
    DESCRIPTION
        "An entry in the rcFlowProfileTable. It contains
        flow informations that testing need."
	INDEX        { rcEtherSamFlowIndex }
    ::={ rcEtherSamFlowTable 1 }

    RcEtherSamFlowEntry ::= SEQUENCE {
	rcEtherSamFlowIndex			         INTEGER,
	rcEtherSamFlowFrameType			     INTEGER,
	rcEtherSamFlowFrameEtherType     INTEGER,
	rcEtherSamFlowFrameLengthType    INTEGER,
	rcEtherSamFlowFrameSize          INTEGER,
	rcEtherSamFlowFrameCvlan         INTEGER,
	rcEtherSamFlowFrameCos           INTEGER,
	rcEtherSamFlowRowStatus          RowStatus,
	rcEtherSamFlowDescription        OCTET STRING,
	rcEtherSamFlowDestAddr    IpAddress,
	rcEtherSamFlowDscp               INTEGER,
	rcEtherSamFlowDatePattern        INTEGER,
	rcEtherSamFlowSourcePort         INTEGER,
	rcEtherSamFlowDestPort    INTEGER,
	rcEtherSamFlowNextHopMac         MacAddress
	}

rcEtherSamFlowIndex        OBJECT-TYPE
    SYNTAX      INTEGER(1..10)
    MAX-ACCESS  not-accessible
    STATUS      current
    DESCRIPTION
            "EtherSam Profile Index"
	::= { rcEtherSamFlowEntry 1 }

rcEtherSamFlowFrameType        OBJECT-TYPE
    SYNTAX      INTEGER{
	            loopback   (1),
	            ethernet   (2),
	            ip         (3),
	            tcp        (4),
                udp        (5),
                video      (6),
                voice-G711 (7),
                voice-G7231 (8),
                voice-G729  (9)
                	            }
    MAX-ACCESS  read-write
    STATUS      current
    DESCRIPTION
            "EtherSam Frame Type"
    DEFVAL{ethernet}
    ::= { rcEtherSamFlowEntry 2 }

rcEtherSamFlowFrameEtherType        OBJECT-TYPE
    SYNTAX      INTEGER
    MAX-ACCESS  read-write
    STATUS      current
    DESCRIPTION
            "Ethertype of etherSam test frame.the default value is 0x08a0"
    DEFVAL{ 2208 }
    ::= { rcEtherSamFlowEntry 3 }

rcEtherSamFlowFrameLengthType        OBJECT-TYPE
    SYNTAX      INTEGER{
	            single    (1),
	            mix       (2)
	            }
    MAX-ACCESS  read-write
    STATUS      current
    DESCRIPTION
            "Ethertype of etherSam test frame."
    DEFVAL{ single }
    ::= { rcEtherSamFlowEntry 4 }

rcEtherSamFlowFrameSize        OBJECT-TYPE
    SYNTAX      INTEGER(64..12288)
    MAX-ACCESS  read-write
    STATUS      current
    DESCRIPTION
            "Frame size of EtherSam single test flow."
    DEFVAL{ 512 }
    ::= { rcEtherSamFlowEntry 5 }

rcEtherSamFlowFrameCvlan        OBJECT-TYPE
    SYNTAX      INTEGER(0..4094)
    MAX-ACCESS  read-write
    STATUS      current
    DESCRIPTION
            "Cvlan of EtherSam Frame."
    DEFVAL{ 0 }
    ::= { rcEtherSamFlowEntry 6 }

rcEtherSamFlowFrameCos        OBJECT-TYPE
    SYNTAX      INTEGER(0..7)
    MAX-ACCESS  read-write
    STATUS      current
    DESCRIPTION
            "cos of EtherSam test flow."
    DEFVAL{ 0 }
    ::= { rcEtherSamFlowEntry 7 }

rcEtherSamFlowRowStatus        OBJECT-TYPE
    SYNTAX      RowStatus
    MAX-ACCESS  read-write
    STATUS      current
    DESCRIPTION
            "Operation status of this table entry."
    ::= { rcEtherSamFlowEntry 8 }

rcEtherSamFlowDescription      OBJECT-TYPE
    SYNTAX      OCTET STRING (SIZE (0..32))
    MAX-ACCESS  read-write
    STATUS      current
    DESCRIPTION
            "The description information of the ethersam flow."
    ::= { rcEtherSamFlowEntry 9 }

rcEtherSamFlowDestAddr      OBJECT-TYPE
    SYNTAX      IpAddress
    MAX-ACCESS  read-write
    STATUS      current
    DESCRIPTION
            "The ethersam flow IP Destination address."
    ::= { rcEtherSamFlowEntry 10 }

rcEtherSamFlowDscp      OBJECT-TYPE
    SYNTAX      INTEGER(0..63)
    MAX-ACCESS  read-write
    STATUS      current
    DESCRIPTION
            "The ethersam flow IP dscp."
     DEFVAL{ 0 }
    ::= { rcEtherSamFlowEntry 11 }

rcEtherSamFlowDatePattern      OBJECT-TYPE
    SYNTAX      INTEGER{null(1),
                  Crc32(2)
                  }
    MAX-ACCESS  read-write
    STATUS      current
    DESCRIPTION
            "This enumeration data type indicates the type of test
            pattern to be sent in an PDU Test TLV.
            The valid enumerated values associated with this type are:
        null(1)       Null signal without CRC-32
        Crc32(2)      signal with CRC-32  "

    DEFVAL{ null }
    ::= { rcEtherSamFlowEntry 12 }

rcEtherSamFlowSourcePort      OBJECT-TYPE
    SYNTAX      INTEGER(0..65535)
    MAX-ACCESS  read-write
    STATUS      current
    DESCRIPTION
            "TCP or UDP frame source port."
    ::= { rcEtherSamFlowEntry 13 }

rcEtherSamFlowDestPort      OBJECT-TYPE
    SYNTAX      INTEGER(0..65535)
    MAX-ACCESS  read-write
    STATUS      current
    DESCRIPTION
            "TCP or UDP frame Destination port."
    ::= { rcEtherSamFlowEntry 14 }

rcEtherSamFlowNextHopMac          OBJECT-TYPE
	SYNTAX      MacAddress
    MAX-ACCESS  read-write
    STATUS      current
    DESCRIPTION
            " L3/L4 frame next Hop Mac"
    ::= { rcEtherSamFlowEntry 15 }


-- rcEtherSamServiceTable
rcEtherSamServiceTable OBJECT-TYPE
    SYNTAX      SEQUENCE OF RcEtherSamServiceEntry
    MAX-ACCESS  not-accessible
    STATUS      current
    DESCRIPTION
        "service information table"

    ::= { rcEtherSamTestGroup 2 }

rcEtherSamServiceEntry        OBJECT-TYPE
	SYNTAX      RcEtherSamServiceEntry
    MAX-ACCESS  not-accessible
    STATUS      current
    DESCRIPTION
        "An entry in the rcCfmMdTable. It contains
         clearing remote MEP database operation."
    INDEX	{ rcEtherSamServiceIndex }
    ::= { rcEtherSamServiceTable 1 }

    RcEtherSamServiceEntry ::= SEQUENCE {
	rcEtherSamServiceIndex					        INTEGER,
	rcEtherSamServiceName					          OCTET STRING,
	rcEtherSamServiceProfileNum		          INTEGER,
	rcEtherSamServiceSvlan                  INTEGER,
	rcEtherSamServiceCos                    INTEGER,
	rcEtherSamServiceUNI                    INTEGER,
	rcEtherSamServiceNNI                    INTEGER,
	rcEtherSamServiceCir                    INTEGER,
	rcEtherSamServiceEir                    INTEGER,
	rcEtherSamServiceMDL                    INTEGER,
	rcEtherSamServiceDMAC                   MacAddress,
	rcEtherSamServiceThresholdAvail         Unsigned32,
	rcEtherSamServiceThresholdFD            Unsigned32,
	rcEtherSamServiceThresholdFDV           Unsigned32,
	rcEtherSamServiceThresholdFLR           Unsigned32,
	rcEtherSamServiceBandWidth              INTEGER,
	rcEtherSamServiceRowStatus              RowStatus,
	rcEtherSamServiceSecondNNI              INTEGER,
	rcEtherSamServiceCfgBypassUniEnable     EnableVar,
	rcEtherSamServiceDIPAddressType         InetAddressType,
	rcEtherSamServiceDIPAddress             InetAddress
}

rcEtherSamServiceIndex          OBJECT-TYPE
    SYNTAX      INTEGER(1..128)
    MAX-ACCESS  not-accessible
    STATUS      current
    DESCRIPTION
            "Index of Service profile.from 1 to 32, those entry can be created but the entries after 32 only can read."
    ::= { rcEtherSamServiceEntry 1 }

rcEtherSamServiceName          OBJECT-TYPE
	SYNTAX      OCTET STRING (SIZE (0..32))
    MAX-ACCESS  read-write
    STATUS      current
    DESCRIPTION
            "Name of Service profile."
    ::= { rcEtherSamServiceEntry 2 }

rcEtherSamServiceProfileNum          OBJECT-TYPE
	SYNTAX      INTEGER(1..10)
    MAX-ACCESS  read-write
    STATUS      current
    DESCRIPTION
            "Number of EtherSam profile."
    ::= { rcEtherSamServiceEntry 3 }

rcEtherSamServiceSvlan          OBJECT-TYPE
	SYNTAX      INTEGER(1..4094)
    MAX-ACCESS  read-write
    STATUS      current
    DESCRIPTION
            "Svlan of service."
    ::= { rcEtherSamServiceEntry 4 }

rcEtherSamServiceCos          OBJECT-TYPE
	SYNTAX      INTEGER(0..7)
    MAX-ACCESS  read-write
    STATUS      current
    DESCRIPTION
            "Stag priority of service."
    ::= { rcEtherSamServiceEntry 5 }

rcEtherSamServiceUNI          OBJECT-TYPE
	SYNTAX      INTEGER
    MAX-ACCESS  read-write
    STATUS      current
    DESCRIPTION
            "UNI of service."
    ::= { rcEtherSamServiceEntry 6 }

rcEtherSamServiceNNI          OBJECT-TYPE
	SYNTAX      INTEGER
    MAX-ACCESS  read-write
    STATUS      current
    DESCRIPTION
            "NNI of service."
    ::= { rcEtherSamServiceEntry 7 }

rcEtherSamServiceCir          OBJECT-TYPE
	SYNTAX      INTEGER(0..1048576)
    MAX-ACCESS  read-write
    STATUS      current
    DESCRIPTION
            "Committed information rate(Kbps)of service."
    ::= { rcEtherSamServiceEntry 8 }

rcEtherSamServiceEir          OBJECT-TYPE
	SYNTAX      INTEGER(0..1048576)
    MAX-ACCESS  read-write
    STATUS      current
    DESCRIPTION
            "Excess information rate(Kbps) of service."
    ::= { rcEtherSamServiceEntry 9 }

rcEtherSamServiceMDL          OBJECT-TYPE
	SYNTAX      INTEGER(0..7)
    MAX-ACCESS  read-write
    STATUS      current
    DESCRIPTION
            "MD level of service."
    ::= { rcEtherSamServiceEntry 10 }

rcEtherSamServiceDMAC          OBJECT-TYPE
	SYNTAX      MacAddress
    MAX-ACCESS  read-write
    STATUS      current
    DESCRIPTION
            "Destination MAC address of service test"
    ::= { rcEtherSamServiceEntry 11 }

rcEtherSamServiceThresholdAvail          OBJECT-TYPE
	SYNTAX      Unsigned32(0..100000)
    MAX-ACCESS  read-write
    STATUS      current
    DESCRIPTION
            "Avail threshold of service test,in milli-percent."
    ::= { rcEtherSamServiceEntry 12 }

rcEtherSamServiceThresholdFD          OBJECT-TYPE
	SYNTAX      Unsigned32(0..1000000)
    MAX-ACCESS  read-write
    STATUS      current
    DESCRIPTION
            "FD threshold of service test,in microseconds."
    ::= { rcEtherSamServiceEntry 13 }

rcEtherSamServiceThresholdFDV          OBJECT-TYPE
	SYNTAX      Unsigned32(0..1000000)
    MAX-ACCESS  read-write
    STATUS      current
    DESCRIPTION
            "FDV threshold of service test,in microseconds."
    ::= { rcEtherSamServiceEntry 14 }

rcEtherSamServiceThresholdFLR          OBJECT-TYPE
	SYNTAX      Unsigned32(0..100000)
    MAX-ACCESS  read-write
    STATUS      current
    DESCRIPTION
            "FLR threshold of service test,in milli-percent."
    ::= { rcEtherSamServiceEntry 15 }

rcEtherSamServiceBandWidth          OBJECT-TYPE
	SYNTAX      INTEGER(0..1048576)
    MAX-ACCESS  read-write
    STATUS      current
    DESCRIPTION
            "Performation bandWidth of service test.if this value is not configed,
            it will be the same as rcEtherSamServiceCir."
    ::= { rcEtherSamServiceEntry 16 }

rcEtherSamServiceRowStatus          OBJECT-TYPE
	SYNTAX      RowStatus
    MAX-ACCESS  read-write
    STATUS      current
    DESCRIPTION
            "Operation status of this table entry."
    ::= { rcEtherSamServiceEntry 17 }

rcEtherSamServiceSecondNNI          OBJECT-TYPE
	SYNTAX      INTEGER
    MAX-ACCESS  read-write
    STATUS      current
    DESCRIPTION
            "The second NNI of the service."
    ::= { rcEtherSamServiceEntry 18 }

rcEtherSamServiceCfgBypassUniEnable OBJECT-TYPE
    SYNTAX      EnableVar
    MAX-ACCESS  read-write
    STATUS      current
    DESCRIPTION
            "This objest controls the test flow whether bypass the uni during the configuration test."
    DEFVAL { disable }
    ::= { rcEtherSamServiceEntry 19 }

rcEtherSamServiceDIPAddressType  OBJECT-TYPE
	    SYNTAX     InetAddressType
	    MAX-ACCESS read-write
	    STATUS     current
	    DESCRIPTION
	       	 	"The type of Internet address for all the objects with SYNTAX
         		InetAddress and  in this entry."
	    ::= { rcEtherSamServiceEntry 20 }

rcEtherSamServiceDIPAddress  OBJECT-TYPE
	    SYNTAX     InetAddress
	    MAX-ACCESS read-write
	    STATUS     current
	    DESCRIPTION
	       	 	"identifying a IP address association remote End Point."
	    ::= { rcEtherSamServiceEntry 21 }

--rcEtherSamCfgResultTable
rcEtherSamCfgResultTable OBJECT-TYPE
    SYNTAX      SEQUENCE OF RcEtherSamCfgResultEntry
    MAX-ACCESS  not-accessible
    STATUS      current
    DESCRIPTION
        "CFM Error CCM Table "

    ::= { rcEtherSamTestGroup 3 }

rcEtherSamCfgResultEntry          OBJECT-TYPE
	SYNTAX      RcEtherSamCfgResultEntry
    MAX-ACCESS  not-accessible
    STATUS      current
    DESCRIPTION
        "An entry in the rcEtherSamCfgResultTable. It contains
        configuration test result.
        "
    INDEX{
    	rcEtherSamServiceIndex,
    	rcEtherSamCfgStepNum
    }
    ::= { rcEtherSamCfgResultTable 1 }

RcEtherSamCfgResultEntry ::= SEQUENCE {
	rcEtherSamCfgStepNum				   INTEGER,
	rcEtherSamCfgResult					   INTEGER,
	rcEtherSamCfgReceiveIR				   INTEGER,
	rcEtherSamCfgFD				           Unsigned32,
	rcEtherSamCfgFDV					   Unsigned32,
	rcEtherSamCfgFLRf				       Unsigned32,
	rcEtherSamCfgFLRb				       Unsigned32
}

rcEtherSamCfgStepNum          		OBJECT-TYPE
	SYNTAX      INTEGER(1..6)
    MAX-ACCESS  not-accessible
    STATUS      current
    DESCRIPTION
            "Step number of EtherSam configuration test."
	::= { rcEtherSamCfgResultEntry 1 }

rcEtherSamCfgResult          		OBJECT-TYPE
	SYNTAX      INTEGER{
	            pass   (1),
	            fail   (2)
	            }
	MAX-ACCESS  read-only
    STATUS      current
    DESCRIPTION
            "the test result of each EtherSam configuration test step."
	::= { rcEtherSamCfgResultEntry 2 }

rcEtherSamCfgReceiveIR          		OBJECT-TYPE
	SYNTAX      INTEGER
	MAX-ACCESS  read-only
    STATUS      current
    DESCRIPTION
            "the information rate receiving."
	::= { rcEtherSamCfgResultEntry 3 }

rcEtherSamCfgFD          		OBJECT-TYPE
	SYNTAX      Unsigned32(0..1000000)
	MAX-ACCESS  read-only
    STATUS      current
    DESCRIPTION
            "Frame Transfer Delay of EtherSam configuration test, in microseconds."
	::= { rcEtherSamCfgResultEntry 4 }

rcEtherSamCfgFDV          		OBJECT-TYPE
	SYNTAX      Unsigned32(0..1000000)
	MAX-ACCESS  read-only
    STATUS      current
    DESCRIPTION
            "Frame Delay Variation of EtherSam configuration test, in microseconds."
	::= { rcEtherSamCfgResultEntry 5 }

rcEtherSamCfgFLRf          		OBJECT-TYPE
	SYNTAX      Unsigned32(0..100000)
	MAX-ACCESS  read-only
    STATUS      current
    DESCRIPTION
            "Forward Frame Loss Ratio of EtherSam configuration test,in milli-percent"
	::= { rcEtherSamCfgResultEntry 6 }

rcEtherSamCfgFLRb          		OBJECT-TYPE
	SYNTAX      Unsigned32(0..100000)
	MAX-ACCESS  read-only
    STATUS      current
    DESCRIPTION
            "Backward Frame Loss Ratio of EtherSam configuration test,in milli-percent."
	::= { rcEtherSamCfgResultEntry 7 }

--rcEtherSamPerformanceResultTable
rcEtherSamPerformanceResultTable OBJECT-TYPE
    SYNTAX      SEQUENCE OF RcEtherSamPerformanceResultEntry
    MAX-ACCESS  not-accessible
    STATUS      current
    DESCRIPTION
        "CFM Error CCM Table "

    ::= { rcEtherSamTestGroup 4 }

rcEtherSamPerformanceResultEntry          OBJECT-TYPE
	SYNTAX      RcEtherSamPerformanceResultEntry
    MAX-ACCESS  not-accessible
    STATUS      current
    DESCRIPTION
        "An entry in the rcEtherSamCfgResultTable. It contains
        configuration test result.
        "
    INDEX{ rcEtherSamServiceIndex }
    ::= { rcEtherSamPerformanceResultTable 1 }

RcEtherSamPerformanceResultEntry ::= SEQUENCE {
	rcEtherSamPerformanceResult				   INTEGER,
	rcEtherSamPerformanceCurrentReceiveIR	   INTEGER,
	rcEtherSamPerformanceMaxReceiveIR		   INTEGER,
	rcEtherSamPerformanceMinReceiveIR		   INTEGER,
	rcEtherSamPerformanceAverageReceiveIR	   INTEGER,
	rcEtherSamPerformanceCurrentFD		       Unsigned32(0..100000),
	rcEtherSamPerformanceMaxFD				   Unsigned32(0..100000),
	rcEtherSamPerformanceMinFD                 Unsigned32(0..100000),
	rcEtherSamPerformanceAverageFD             Unsigned32(0..100000),
	rcEtherSamPerformanceCurrentFDV            Unsigned32(0..100000),
	rcEtherSamPerformanceMaxFDV                Unsigned32(0..100000),
	rcEtherSamPerformanceMinFDV                Unsigned32(0..100000),
	rcEtherSamPerformanceAverageFDV            Unsigned32(0..100000),
	rcEtherSamPerformanceCurrentFLRf           Unsigned32(0..100000),
	rcEtherSamPerformanceMaxFLRf               Unsigned32(0..100000),
	rcEtherSamPerformanceMinFLRf               Unsigned32(0..100000),
	rcEtherSamPerformanceAverageFLRf           Unsigned32(0..100000),
	rcEtherSamPerformanceCurrentFLRb           Unsigned32(0..100000),
	rcEtherSamPerformanceMaxFLRb               Unsigned32(0..100000),
	rcEtherSamPerformanceMinFLRb               Unsigned32(0..100000),
	rcEtherSamPerformanceAverageFLRb           Unsigned32(0..100000),
	rcEtherSamPerformanceAvail                 Unsigned32(0..100000)
}

rcEtherSamPerformanceResult          		OBJECT-TYPE
	SYNTAX      INTEGER{
	            pass    (1),
	            fail    (2)
	            }
    MAX-ACCESS  read-only
    STATUS      current
    DESCRIPTION
            "result of EtherSam Performance test."
	::= { rcEtherSamPerformanceResultEntry 1 }

rcEtherSamPerformanceCurrentReceiveIR          		OBJECT-TYPE
	SYNTAX      INTEGER
	MAX-ACCESS  read-only
    STATUS      current
    DESCRIPTION
            "EtherSam PerformanceTest Current Receive Information Rate, in Kpbs."
	::= { rcEtherSamPerformanceResultEntry 2 }

rcEtherSamPerformanceMaxReceiveIR          		OBJECT-TYPE
	SYNTAX      INTEGER
	MAX-ACCESS  read-only
    STATUS      current
    DESCRIPTION
            "EtherSam PerformanceTest max Receive Information Rate, in Kpbs."
	::= { rcEtherSamPerformanceResultEntry 3 }

rcEtherSamPerformanceMinReceiveIR          		OBJECT-TYPE
	SYNTAX      INTEGER
	MAX-ACCESS  read-only
    STATUS      current
    DESCRIPTION
            "EtherSam PerformanceTest min Receive Information Rate, in Kpbs."
	::= { rcEtherSamPerformanceResultEntry 4 }

rcEtherSamPerformanceAverageReceiveIR          		OBJECT-TYPE
	SYNTAX      INTEGER
	MAX-ACCESS  read-only
    STATUS      current
    DESCRIPTION
            "EtherSam PerformanceTest Average Receive Information Rate, in Kpbs."
	::= { rcEtherSamPerformanceResultEntry 5 }

rcEtherSamPerformanceCurrentFD          		OBJECT-TYPE
	SYNTAX      Unsigned32(0..1000000)
	MAX-ACCESS  read-only
    STATUS      current
    DESCRIPTION
            "current Transfer Delay of EtherSam Performance test, in microseconds."
	::= { rcEtherSamPerformanceResultEntry 6 }

rcEtherSamPerformanceMaxFD          		OBJECT-TYPE
	SYNTAX      Unsigned32(0..1000000)
	MAX-ACCESS  read-only
    STATUS      current
    DESCRIPTION
            "max Transfer Delay of EtherSam Performance test, in microseconds."
	::= { rcEtherSamPerformanceResultEntry 7 }

rcEtherSamPerformanceMinFD          		OBJECT-TYPE
	SYNTAX      Unsigned32(0..1000000)
	MAX-ACCESS  read-only
    STATUS      current
    DESCRIPTION
            "min Transfer Delay of EtherSam Performance test, in microseconds."
	::= { rcEtherSamPerformanceResultEntry 8 }

rcEtherSamPerformanceAverageFD          		OBJECT-TYPE
	SYNTAX      Unsigned32(0..1000000)
	MAX-ACCESS  read-only
    STATUS      current
    DESCRIPTION
            "Average Transfer Delay of EtherSam Performance test, in microseconds."
	::= { rcEtherSamPerformanceResultEntry 9 }

rcEtherSamPerformanceCurrentFDV          		OBJECT-TYPE
	SYNTAX      Unsigned32(0..1000000)
	MAX-ACCESS  read-only
    STATUS      current
    DESCRIPTION
            "Current Frame Delay Variation of EtherSam Performance test, in microseconds."
	::= { rcEtherSamPerformanceResultEntry 10 }

rcEtherSamPerformanceMaxFDV          		OBJECT-TYPE
	SYNTAX      Unsigned32(0..1000000)
	MAX-ACCESS  read-only
    STATUS      current
    DESCRIPTION
            "max Frame Delay Variation of EtherSam Performance test, in microseconds."
	::= { rcEtherSamPerformanceResultEntry 11 }

rcEtherSamPerformanceMinFDV          		OBJECT-TYPE
	SYNTAX      Unsigned32(0..1000000)
	MAX-ACCESS  read-only
    STATUS      current
    DESCRIPTION
            "min Frame Delay Variation of EtherSam Performance test, in microseconds."
	::= { rcEtherSamPerformanceResultEntry 12 }

rcEtherSamPerformanceAverageFDV          		OBJECT-TYPE
	SYNTAX      Unsigned32(0..1000000)
	MAX-ACCESS  read-only
    STATUS      current
    DESCRIPTION
            "Average Frame Delay Variation of EtherSam Performance test, in microseconds."
	::= { rcEtherSamPerformanceResultEntry 13 }

rcEtherSamPerformanceCurrentFLRf          		OBJECT-TYPE
	SYNTAX      Unsigned32(0..100000)
	MAX-ACCESS  read-only
    STATUS      current
    DESCRIPTION
            "Current forward Frame Loss Ratio of EtherSam Performance test, in milli-percent."
	::= { rcEtherSamPerformanceResultEntry 14 }

rcEtherSamPerformanceMaxFLRf          		OBJECT-TYPE
	SYNTAX      Unsigned32(0..100000)
	MAX-ACCESS  read-only
    STATUS      current
    DESCRIPTION
            "max forward Frame Loss Ratio of EtherSam Performance test, in milli-percent."
	::= { rcEtherSamPerformanceResultEntry 15 }

rcEtherSamPerformanceMinFLRf          		OBJECT-TYPE
	SYNTAX      Unsigned32(0..100000)
	MAX-ACCESS  read-only
    STATUS      current
    DESCRIPTION
            "min forward Frame Loss Ratio of EtherSam Performance test, in milli-percent."
	::= { rcEtherSamPerformanceResultEntry 16 }

rcEtherSamPerformanceAverageFLRf          		OBJECT-TYPE
	SYNTAX      Unsigned32(0..100000)
	MAX-ACCESS  read-only
    STATUS      current
    DESCRIPTION
            "Average forward Frame Loss Ratio of EtherSam Performance test, in milli-percent."
	::= { rcEtherSamPerformanceResultEntry 17 }

rcEtherSamPerformanceCurrentFLRb          		OBJECT-TYPE
	SYNTAX      Unsigned32(0..100000)
	MAX-ACCESS  read-only
    STATUS      current
    DESCRIPTION
            "Current backward  Frame Loss Ratio of EtherSam Performance test, in milli-percent."
	::= { rcEtherSamPerformanceResultEntry 18 }

rcEtherSamPerformanceMaxFLRb          		OBJECT-TYPE
	SYNTAX      Unsigned32(0..100000)
	MAX-ACCESS  read-only
    STATUS      current
    DESCRIPTION
            "max backward Frame Loss Ratio of EtherSam Performance test, in milli-percent."
	::= { rcEtherSamPerformanceResultEntry 19 }

rcEtherSamPerformanceMinFLRb          		OBJECT-TYPE
	SYNTAX      Unsigned32(0..100000)
	MAX-ACCESS  read-only
    STATUS      current
    DESCRIPTION
            "min backward Frame Loss Ratio of EtherSam Performance test, in milli-percent."
	::= { rcEtherSamPerformanceResultEntry 20 }

rcEtherSamPerformanceAverageFLRb          		OBJECT-TYPE
	SYNTAX      Unsigned32(0..100000)
	MAX-ACCESS  read-only
    STATUS      current
    DESCRIPTION
            "Average backward Frame Loss Ratio of EtherSam Performance test, in milli-percent."
	::= { rcEtherSamPerformanceResultEntry 21 }

rcEtherSamPerformanceAvail          		OBJECT-TYPE
	SYNTAX      Unsigned32(0..100000)
	MAX-ACCESS  read-only
    STATUS      current
    DESCRIPTION
            "EtherSam Performance test Avail, in milli-percent."
	::= { rcEtherSamPerformanceResultEntry 22 }

--rcEtherSamStatisticTable
rcEtherSamStatisticTable OBJECT-TYPE
    SYNTAX      SEQUENCE OF RcEtherSamStatisticEntry
    MAX-ACCESS  not-accessible
    STATUS      current
    DESCRIPTION
        "ethersam statistic talble. "
    ::= { rcEtherSamTestGroup 5 }

rcEtherSamStatisticEntry          OBJECT-TYPE
	SYNTAX      RcEtherSamStatisticEntry
    MAX-ACCESS  not-accessible
    STATUS      current
    DESCRIPTION
        "An entry in the rcEtherSamStatisticTable. It contains
        test frame statistic informations.
        "
    INDEX{ rcEtherSamServiceIndex }
    ::= { rcEtherSamStatisticTable 1 }

RcEtherSamStatisticEntry ::= SEQUENCE {
	rcEtherSamStatisticDropEvents         Counter32,
	rcEtherSamStatisticCRCAlignErrors     Counter32,
	rcEtherSamStatisticUndersizePkts      Counter32,
	rcEtherSamStatisticFragments          Counter32,
	rcEtherSamStatisticJabbers            Counter32,
	rcEtherSamStatisticCollisions         Counter32,
	rcEtherSamStatisticInUnicast          Counter64,
	rcEtherSamStatisticInMulticast        Counter64,
	rcEtherSamStatisticInBroadcast        Counter64,
	rcEtherSamStatisticOutUnicast         Counter64,
	rcEtherSamStatisticOutMulticast       Counter64,
	rcEtherSamStatisticOutBroadcast       Counter64,
	rcEtherSamStatistic64to127octets      Counter64,
	rcEtherSamStatistic128to255octets     Counter64,
	rcEtherSamStatistic256to511octets     Counter64,
	rcEtherSamStatistic512to1023octets    Counter64,
	rcEtherSamStatistic1024to1518Octet    Counter64,
	rcEtherSamStatistic1519Octet          Counter64
}

rcEtherSamStatisticDropEvents          		OBJECT-TYPE
	SYNTAX      Counter32
    MAX-ACCESS  read-only
    STATUS      current
    DESCRIPTION
            "Statistic of drop events."
	::= { rcEtherSamStatisticEntry 1 }

rcEtherSamStatisticCRCAlignErrors          		OBJECT-TYPE
	SYNTAX      Counter32
    MAX-ACCESS  read-only
    STATUS      current
    DESCRIPTION
            "Statistic of CRCAlignErrors"
	::= { rcEtherSamStatisticEntry 2 }

rcEtherSamStatisticUndersizePkts          		OBJECT-TYPE
	SYNTAX      Counter32
    MAX-ACCESS  read-only
    STATUS      current
    DESCRIPTION
            "Statistic of UndersizePkts"
	::= { rcEtherSamStatisticEntry 3 }

rcEtherSamStatisticFragments          		OBJECT-TYPE
	SYNTAX      Counter32
    MAX-ACCESS  read-only
    STATUS      current
    DESCRIPTION
            "Statistic of Fragments."
	::= { rcEtherSamStatisticEntry 4 }

rcEtherSamStatisticJabbers          		OBJECT-TYPE
	SYNTAX      Counter32
    MAX-ACCESS  read-only
    STATUS      current
    DESCRIPTION
            "Statistic of Jabbers"
	::= { rcEtherSamStatisticEntry 5 }

rcEtherSamStatisticCollisions          		OBJECT-TYPE
	SYNTAX      Counter32
    MAX-ACCESS  read-only
    STATUS      current
    DESCRIPTION
            "Statistic of Collisions"
	::= { rcEtherSamStatisticEntry 6 }

rcEtherSamStatisticInUnicast          		OBJECT-TYPE
	SYNTAX      Counter64
    MAX-ACCESS  read-only
    STATUS      current
    DESCRIPTION
            "Statistic of unicast packets receiving."
	::= { rcEtherSamStatisticEntry 7 }

rcEtherSamStatisticInMulticast         		OBJECT-TYPE
	SYNTAX      Counter64
    MAX-ACCESS  read-only
    STATUS      current
    DESCRIPTION
            "Statistic of multicast packets receiving."
	::= { rcEtherSamStatisticEntry 8 }

rcEtherSamStatisticInBroadcast         		OBJECT-TYPE
	SYNTAX      Counter64
    MAX-ACCESS  read-only
    STATUS      current
    DESCRIPTION
            "Statistic of broadcast packets receiving."
	::= { rcEtherSamStatisticEntry 9 }

rcEtherSamStatisticOutUnicast          		OBJECT-TYPE
	SYNTAX      Counter64
    MAX-ACCESS  read-only
    STATUS      current
    DESCRIPTION
            "Statistic of unicast packets transmited."
	::= { rcEtherSamStatisticEntry 10 }

rcEtherSamStatisticOutMulticast        		OBJECT-TYPE
	SYNTAX      Counter64
    MAX-ACCESS  read-only
    STATUS      current
    DESCRIPTION
            "Statistic of multicast packets transmited."
	::= { rcEtherSamStatisticEntry 11 }

rcEtherSamStatisticOutBroadcast        		OBJECT-TYPE
	SYNTAX      Counter64
    MAX-ACCESS  read-only
    STATUS      current
    DESCRIPTION
            "Statistic of broadcast packets transmited."
	::= { rcEtherSamStatisticEntry 12 }

rcEtherSamStatistic64to127octets       		OBJECT-TYPE
	SYNTAX      Counter64
    MAX-ACCESS  read-only
    STATUS      current
    DESCRIPTION
            "Statistic packets from 64 Byte to 127 Byte ."
	::= { rcEtherSamStatisticEntry 13 }

rcEtherSamStatistic128to255octets      		OBJECT-TYPE
	SYNTAX      Counter64
    MAX-ACCESS  read-only
    STATUS      current
    DESCRIPTION
            "Statistic packets from 128 Byte to 255 Byte ."
	::= { rcEtherSamStatisticEntry 14 }

rcEtherSamStatistic256to511octets      		OBJECT-TYPE
	SYNTAX      Counter64
    MAX-ACCESS  read-only
    STATUS      current
    DESCRIPTION
            "Statistic packets from 256 Byte to 511 Byte ."
	::= { rcEtherSamStatisticEntry 15 }

rcEtherSamStatistic512to1023octets      		OBJECT-TYPE
	SYNTAX      Counter64
    MAX-ACCESS  read-only
    STATUS      current
    DESCRIPTION
            "Statistic packets from 512 Byte to 1023 Byte ."
	::= { rcEtherSamStatisticEntry 16 }

rcEtherSamStatistic1024to1518Octet      		OBJECT-TYPE
	SYNTAX      Counter64
    MAX-ACCESS  read-only
    STATUS      current
    DESCRIPTION
            "Statistic packets from 1024 Byte to 1518 Byte ."
	::= { rcEtherSamStatisticEntry 17 }

rcEtherSamStatistic1519Octet      		OBJECT-TYPE
	SYNTAX      Counter64
    MAX-ACCESS  read-only
    STATUS      current
    DESCRIPTION
            "Statistic packets larger than 1518 Byte ."
	::= { rcEtherSamStatisticEntry 18 }


-- rcEtherSam2544ResultTable
-- rcEtherSam2544ResultEntry
--rcEtherSam2544FrameSize
--rcEtherSam2544Rate
--rcEtherSam2544BER
--rcEtherSam2544FD
--rcEtherSam2544FDV

rcEtherSam2544ResultTable OBJECT-TYPE
    SYNTAX      SEQUENCE OF RcEtherSam2544ResultEntry
    MAX-ACCESS  not-accessible
    STATUS      current
    DESCRIPTION
        "ethersam rfc2544 test result talble. "
    ::= { rcEtherSamTestGroup 6 }

rcEtherSam2544ResultEntry          OBJECT-TYPE
	SYNTAX      RcEtherSam2544ResultEntry
    MAX-ACCESS  not-accessible
    STATUS      current
    DESCRIPTION
        "An entry in the rcEtherSam2544ResultTable. It contains rfc2544
        test result informations.
        "
    INDEX{ rcEtherSamServiceIndex, rcEtherSam2544FrameSize}
    ::= { rcEtherSam2544ResultTable 1 }

RcEtherSam2544ResultEntry ::= SEQUENCE {
	rcEtherSam2544FrameSize         INTEGER,
	rcEtherSam2544Rate              INTEGER,
	rcEtherSam2544BER               INTEGER,
	rcEtherSam2544FD                INTEGER,
	rcEtherSam2544FDV               INTEGER
	}

rcEtherSam2544FrameSize      		OBJECT-TYPE
	SYNTAX      INTEGER
    MAX-ACCESS  not-accessible
    STATUS      current
    DESCRIPTION
            "Test flow frame length."
	::= { rcEtherSam2544ResultEntry 1 }

rcEtherSam2544Rate      		OBJECT-TYPE
	SYNTAX      INTEGER
    MAX-ACCESS  read-only
    STATUS      current
    DESCRIPTION
            "The flow throughput."
	::= { rcEtherSam2544ResultEntry 2 }

rcEtherSam2544BER      		OBJECT-TYPE
	SYNTAX      INTEGER
    MAX-ACCESS  read-only
    STATUS      current
    DESCRIPTION
            "The flow bit error rate."
	::= { rcEtherSam2544ResultEntry 3 }

rcEtherSam2544FD      		OBJECT-TYPE
	SYNTAX      INTEGER
    MAX-ACCESS  read-only
    STATUS      current
    DESCRIPTION
            "The flow frame delay."
	::= { rcEtherSam2544ResultEntry 4 }

rcEtherSam2544FDV      		OBJECT-TYPE
	SYNTAX      INTEGER
    MAX-ACCESS  read-only
    STATUS      current
    DESCRIPTION
            "The flow frame delay variation."
	::= { rcEtherSam2544ResultEntry 5 }

--rcEtherSamFlowFrameLengthTable
--rcEtherSamFlowFrameLengthEntry
--rcEtherSamFlowFrameNum
--rcEtherSamFlowFrame1
--rcEtherSamFlowFrame2
--rcEtherSamFlowFrame3
--rcEtherSamFlowFrame4
--rcEtherSamFlowFrame5
--rcEtherSamFlowFrame6

rcEtherSamFlowFrameLengthTable OBJECT-TYPE
    SYNTAX      SEQUENCE OF RcEtherSamFlowFrameLengthEntry
    MAX-ACCESS  not-accessible
    STATUS      current
    DESCRIPTION
        "ethersam farme length talble. "
    ::= { rcEtherSamTestGroup 7 }

rcEtherSamFlowFrameLengthEntry          OBJECT-TYPE
	SYNTAX      RcEtherSamFlowFrameLengthEntry
    MAX-ACCESS  not-accessible
    STATUS      current
    DESCRIPTION
        "An entry in the rcEtherSamFlowFrameLengthTable. It contains frame length informations.
        "
    INDEX{ rcEtherSamFlowIndex}
    ::= { rcEtherSamFlowFrameLengthTable 1 }

RcEtherSamFlowFrameLengthEntry ::= SEQUENCE {
	rcEtherSamFlowFrameNum            INTEGER,
	rcEtherSamFlowFrame1              INTEGER,
	rcEtherSamFlowFrame2              INTEGER,
	rcEtherSamFlowFrame3              INTEGER,
	rcEtherSamFlowFrame4              INTEGER,
	rcEtherSamFlowFrame5              INTEGER,
	rcEtherSamFlowFrame6              INTEGER
	}

rcEtherSamFlowFrameNum      		OBJECT-TYPE
	SYNTAX      INTEGER(1..6)
    MAX-ACCESS  read-write
    STATUS      current
    DESCRIPTION
            "The number of flow frame."
	::= { rcEtherSamFlowFrameLengthEntry 1 }

rcEtherSamFlowFrame1      		OBJECT-TYPE
	SYNTAX      INTEGER(64..12288)
    MAX-ACCESS  read-write
    STATUS      current
    DESCRIPTION
            "EtherSam flow frame length."
	::= { rcEtherSamFlowFrameLengthEntry 2 }

rcEtherSamFlowFrame2      		OBJECT-TYPE
	SYNTAX      INTEGER(64..12288)
    MAX-ACCESS  read-write
    STATUS      current
    DESCRIPTION
            "EtherSam flow frame length."
	::= { rcEtherSamFlowFrameLengthEntry 3 }

rcEtherSamFlowFrame3      		OBJECT-TYPE
	SYNTAX      INTEGER(64..12288)
    MAX-ACCESS  read-write
    STATUS      current
    DESCRIPTION
            "EtherSam flow frame length."
	::= { rcEtherSamFlowFrameLengthEntry 4 }

rcEtherSamFlowFrame4      		OBJECT-TYPE
	SYNTAX      INTEGER(64..12288)
    MAX-ACCESS  read-write
    STATUS      current
    DESCRIPTION
            "EtherSam flow frame length."
	::= { rcEtherSamFlowFrameLengthEntry 5 }

rcEtherSamFlowFrame5      		OBJECT-TYPE
	SYNTAX      INTEGER(64..12288)
    MAX-ACCESS  read-write
    STATUS      current
    DESCRIPTION
            "EtherSam flow frame length."
	::= { rcEtherSamFlowFrameLengthEntry 6 }

rcEtherSamFlowFrame6      		OBJECT-TYPE
	SYNTAX      INTEGER(64..12288)
    MAX-ACCESS  read-write
    STATUS      current
    DESCRIPTION
            "EtherSam flow frame length."
	::= { rcEtherSamFlowFrameLengthEntry 7 }

-- rcEtherSamTestTrapGroup
--rcEtherSamServiceTestFailTrap
--rcEtherSamServiceFinishTrap
--rcEtherSam2544FinishTrap

rcEtherSamServiceTestFailTrap
NOTIFICATION-TYPE
    OBJECTS     { rcEtherSamServiceIndex
                }
    STATUS      current
    DESCRIPTION
       "when the test result is FAIL, the trap will be sent.
        and the rcEtherSamServiceIndex points out which service."
    ::= { rcEtherSamTestTrapGroup 1 }

rcEtherSamServiceFinishTrap
NOTIFICATION-TYPE
    OBJECTS     { rcEtherSamServiceTestResult
                }
    STATUS      current
    DESCRIPTION
       "when all services test are finish, the trap will be sent,
        and the  rcEtherSamServiceResult will show the test result."
    ::= { rcEtherSamTestTrapGroup 2 }

rcEtherSam2544FinishTrap
NOTIFICATION-TYPE
    OBJECTS     { rcEtherSamServiceList
                }
    STATUS      current
    DESCRIPTION
       "when rfc2544 test is finish, the trap will be sent,
        and the  rcEtherSamServiceList will show which service do the test."
    ::= { rcEtherSamTestTrapGroup 3 }

END
