--MibName=raisecomClkmgmt
-- *****************************************************************
-- Version 1.0 Created 2010.10.14 by zengliang
-- This version of MIB is created just for the Management of ES-SUB-CLK.
--
-- Copyright(c) 2002-2012 by RAISECOM TECH, Ltd.
-- All rights reserved.
--
-- modify history
--
-- *****************************************************************
SWITCH-CLKMGMT-MIB  DEFINITIONS ::= BEGIN

IMPORTS
        raisecomAgent
            FROM RAISECOM-BASE-MIB
        EnableVar
            FROM SWITCH-TC
        Integer32, Unsigned32,IpAddress
        	FROM SNMPv2-SMI;

	raisecomClkmgmt MODULE-IDENTITY
        LAST-UPDATED    "201010140000Z"
        ORGANIZATION    "Raisecom, Inc."
        CONTACT-INFO
                "       Raise Systems

                Postal: Beijing,
                        China

                   Tel: 86-010-82884499

                E-mail: support@raisecom.com"
        DESCRIPTION
                "Configuration of clkmgmt object."
-- -------------------------------------------------------------
-- modify history
-- -------------------------------------------------------------
        REVISION    "201010140000Z"
        DESCRIPTION "The initial revision of this MIB."
                ::= { raisecomAgent 21}

-- -------------------------------------------------------------
-- groups in the SWITCH-CLKMGMT MIB
-- -------------------------------------------------------------

-- -------------------------------------------------------------
-- raisecomClkmgmt2mPortTable
-- -------------------------------------------------------------

    raisecomClkmgmt2mPortTable OBJECT-TYPE
        SYNTAX SEQUENCE OF raisecomClkmgmt2mPortEntry
        MAX-ACCESS not-accessible
        STATUS current
        DESCRIPTION
            "Clock-management 2m port table."
        ::= { raisecomClkmgmt 1 }

    raisecomClkmgmt2mPortEntry OBJECT-TYPE
        SYNTAX raisecomClkmgmt2mPortEntry
        MAX-ACCESS not-accessible
        STATUS current
        DESCRIPTION
            "Clock-management 2m port table entry."
        INDEX { raisecomClkmgmt2mPortIndex }
        ::= { raisecomClkmgmt2mPortTable 1 }

    raisecomClkmgmt2mPortEntry ::= SEQUENCE {
        raisecomClkmgmt2mPortIndex            Unsigned32,
        raisecomClkmgmt2mPortMode             INTEGER,
        raisecomClkmgmt2mPortE1SaBit           INTEGER,
    }

    raisecomClkmgmt2mPortIndex OBJECT-TYPE
        SYNTAX  Unsigned32
        MAX-ACCESS not-accessible
        STATUS current
        DESCRIPTION
            "Clock management 2m port index."
        ::= { raisecomClkmgmt2mPortEntry 1 }

    raisecomClkmgmt2mPortMode OBJECT-TYPE
        SYNTAX	INTEGER
        {
        	clk-2mHz(1),
        	clk-E1(2),
        	clk-E1-CRC(3)
        }
        MAX-ACCESS read-write
        STATUS current
        DESCRIPTION
            "Mode of 2m port."
        ::= { raisecomClkmgmt2mPortEntry 2 }

    raisecomClkmgmt2mPortE1SaBit OBJECT-TYPE
        SYNTAX  INTEGER(4..8)
        MAX-ACCESS read-write
        STATUS current
        DESCRIPTION
            "Sa bit"
        ::= { raisecomClkmgmt2mPortEntry 3 }

END
