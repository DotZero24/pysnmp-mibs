--MibName=raisecomPortStat
-- *****************************************************************
-- RAISECOM-PORTSTATISTIC-MIB.mib:  Raisecom port statistic MIB file
--
-- Feb 2012, huzhiwen
--
-- Copyright (c) 1996-2009 by Raisecom Technology Co., Ltd.
-- All rights reserved.
--
-- *****************************************************************
RAISECOM-PORTSTATISTIC-MIB  DEFINITIONS ::= BEGIN

IMPORTS
       INTEGER,Unsigned32           FROM SNMPv2-SMI
       EnableVar					FROM SWITCH-TC
       raisecomAgent	            FROM RAISECOM-BASE-MIB;

	raisecomPortStat MODULE-IDENTITY
        LAST-UPDATED    "201202280000Z"
        ORGANIZATION    "Raisecom Technology Co., Ltd."
        CONTACT-INFO
            	     "Raisecom Science & Technology Co., ltd.
             	     Phone:  01082884499
             	     Email:  support@raisecom.com"
        DESCRIPTION
                "description of raisecomPortStat object."
                 REVISION   "201202280000Z"
                 DESCRIPTION
                "port statistic mib."
                ::= { raisecomAgent 77 }

------------------------------------------------------------------
-- components of this MIB.
------------------------------------------------------------------
    raisecomPortStatNotifications   OBJECT IDENTIFIER
                                ::= { raisecomPortStat 1 }
        raisecomPortStatTrafficTrap OBJECT IDENTIFIER
                                ::= { raisecomPortStatNotifications 1 }
    raisecomPortStatObject          OBJECT IDENTIFIER
                                ::= { raisecomPortStat 2 }
    raisecomPortStatScalar          OBJECT IDENTIFIER
                                ::= { raisecomPortStatObject 1 }

    raisecomPortStatConformance     OBJECT IDENTIFIER
                                ::= { raisecomPortStat 3 }

------------------------------------------------------------------
-- Notifications
------------------------------------------------------------------
raisecomPortStatIngressTrafficAlarmTrap NOTIFICATION-TYPE

        OBJECTS {raisecomPortStatIngressRate}
		STATUS current
		DESCRIPTION
				"When the ingress traffic of a port beyond the threshold, the  trap  will
				be raised and OLT will notify this event to the NMS. "
		::= { raisecomPortStatTrafficTrap 1 }

raisecomPortStatIngressTrafficRecoverTrap NOTIFICATION-TYPE

        OBJECTS {raisecomPortStatIngressRate}
		STATUS current
		DESCRIPTION
				"When the ingress traffic of a port under the threshold, the  trap  will
				be raised and OLT will notify this event to the NMS. "
		::= { raisecomPortStatTrafficTrap 2 }

raisecomPortStatEgressTrafficAlarmTrap NOTIFICATION-TYPE

        OBJECTS {raisecomPortStatEgressRate}
		STATUS current
		DESCRIPTION
				"When the egress traffic of a port beyond the threshold, the  trap  will
				be raised and OLT will notify this event to the NMS. "
		::= { raisecomPortStatTrafficTrap 3 }


raisecomPortStatEgressTrafficRecoverTrap NOTIFICATION-TYPE

        OBJECTS {raisecomPortStatEgressRate}
		STATUS current
		DESCRIPTION
				"When the egress traffic of a port under the threshold, the  trap  will
				be raised and OLT will notify this event to the NMS. "
		::= { raisecomPortStatTrafficTrap 4 }

------------------------------------------------------------------
-- Scalar
------------------------------------------------------------------

raisecomPortStatTrafficInterval OBJECT-TYPE
    	SYNTAX   INTEGER  (1..3600)
    	MAX-ACCESS  read-write
    	STATUS      current
    	DESCRIPTION
              "This object indicates the Interval of Port Traffic statistics."
        ::= { raisecomPortStatScalar 1 }

------------------------------------------------------------------
-- raisecomPortStatTable
------------------------------------------------------------------

    raisecomPortStatTable OBJECT-TYPE
        SYNTAX SEQUENCE OF raisecomPortStatEntry
        MAX-ACCESS not-accessible
        STATUS current
        DESCRIPTION
            "A table of port statistic."
        ::= { raisecomPortStatObject 2 }

    raisecomPortStatEntry OBJECT-TYPE
        SYNTAX raisecomPortStatEntry
        MAX-ACCESS not-accessible
        STATUS current
        DESCRIPTION
            "Table entry of port statistic."
        INDEX { raisecomPortStatIndex }
        ::= { raisecomPortStatTable 1 }

    raisecomPortStatEntry ::= SEQUENCE
    {
        raisecomPortStatIndex                   INTEGER,
        raisecomPortStatIngressRate		        Unsigned32,
        raisecomPortStatEgressRate		        Unsigned32,
        raisecomPortStatRateEnable              EnableVar,
        raisecomPortStatIngressRateThreshold    Unsigned32,
        raisecomPortStatEgressRateThreshold     Unsigned32,
        raisecomPortStatTrafficAlarmDescr       OCTET STRING
    }

   	raisecomPortStatIndex OBJECT-TYPE
        SYNTAX INTEGER
        MAX-ACCESS not-accessible
        STATUS current
        DESCRIPTION
            "This object indicates the index of a port."
        ::= { raisecomPortStatEntry 1 }

   	raisecomPortStatIngressRate OBJECT-TYPE
        SYNTAX Unsigned32
        UNITS     "kbps"
        ACCESS read-only
        STATUS current
        DESCRIPTION
                "This object indicates the Ingress rate  of the port. "
        ::= { raisecomPortStatEntry 2 }

   	raisecomPortStatEgressRate OBJECT-TYPE
        SYNTAX  Unsigned32
        UNITS     "kbps"
        ACCESS read-only
        STATUS current
        DESCRIPTION
                "This object indicates the Egress rate  of the port. "
        ::= { raisecomPortStatEntry 3 }

    raisecomPortStatRateEnable OBJECT-TYPE
    	SYNTAX   EnableVar
    	MAX-ACCESS  read-write
    	STATUS      current
    	DESCRIPTION
              "Enable or disable the rate statistics of port. "
        ::= { raisecomPortStatEntry 4 }

   	raisecomPortStatIngressRateThreshold OBJECT-TYPE
        SYNTAX Unsigned32
        UNITS     "kbps"
        ACCESS read-write
        STATUS current
        DESCRIPTION
                "This object indicates the Ingress rate threshold of the port. "
        ::= { raisecomPortStatEntry 5 }

   	raisecomPortStatEgressRateThreshold OBJECT-TYPE
        SYNTAX Unsigned32
        UNITS     "kbps"
        ACCESS read-write
        STATUS current
        DESCRIPTION
                "This object indicates the egress rate  threshold of the port. "
        ::= { raisecomPortStatEntry 6 }

    raisecomPortStatTrafficAlarmDescr OBJECT-TYPE
        SYNTAX OCTET STRING (SIZE (0..64))
        ACCESS read-only
        STATUS current
        DESCRIPTION
                "The description of traffic alarm information. "
        ::= { raisecomPortStatEntry 7 }

 END
