-- =======================================================================
-- RAISECOM-OPTICAL-UDETH-INTERFACE-MIB.my
--
-- Version info
--
-- Copyright(c) 2003-2005 by RAISECOM TECH, Ltd.
-- All rights reserved.
-- =======================================================================

--在rcOptUdEthInterfaceMaxFrameLen中添加新选项1632，add by sujun 20130506


RAISECOM-OPTICAL-UDETH-INTERFACE-MIB  DEFINITIONS ::= BEGIN

IMPORTS
        MODULE-IDENTITY, OBJECT-TYPE,NOTIFICATION-TYPE,Integer32
        	FROM SNMPv2-SMI
        DisplayString
            FROM SNMPv2-TC
        ifIndex
            FROM IF-MIB
        optUdSysMgmt
            FROM RAISECOM-BASE-MIB
        RcOptIfModuleType
            FROM RAISECOM-OPTICAL-MODULE-TYPE-MIB
        rcNotifsTrapLocation
                FROM RAISECOM-NOTIFICATION-MIB
        rcEntPhysicalID
                FROM RAISECOM-OPTICAL-ENTITY-MIB;
		raisecomOptUdEthInterfaceMib   MODULE-IDENTITY

        LAST-UPDATED "1307090000Z"
        ORGANIZATION "RaiseCom Technology CO.,LTD"
        CONTACT-INFO
           "           "
        DESCRIPTION
              "The MIB module to describe Ether interface objects."
		REVISION      "0711290000Z"
		DESCRIPTION
		"
		初始版本，由RAISECOM-OPTICAL-ETH-INTERFACE-MIB.my修改得来
		1、增加rcEntPhysicalID作为索引
		2、增加rcOptUdEthInterfaceMaxFrameLength,按字节数指定最大帧长
		3、增加rcOptUdEthIfStatisticTable,表项基本参照IF-MIB中的统计信息
		4、增加rcOptUdEthlinkDownTrap、rcOptUdEthlinkUpTrap
		"
		REVISION      "0801020000Z"
		DESCRIPTION
		"
		同步RAISECOM-OPTICAL-ETH-INTERFACE-MIB.my所做修改，增加rcOptUdEthInterfaceBandwidth、rcOptUdEthInterfaceBandwidthStatus、rcOptUdEthInterfaceCheckLoopbackStatus、rcOptUdEthInterfaceCheckLoopback、rcOptUdEthInterfaceModuleType
		"
		REVISION      "0802150000Z"
		DESCRIPTION
		"
		同步RAISECOM-OPTICAL-ETH-INTERFACE-MIB.my所做修改,增加
		rcOptUdEthInterfaceRxBandwidth             发送带宽配置
		rcOptUdEthInterfaceRxBandwidthStatus       发送带宽状态
		rcOptUdEthInterfaceTxBandwidth             接收带宽配置
		rcOptUdEthInterfaceTxBandwidthStatus       接收带宽状态
		"
		REVISION      "0903160000Z"
		DESCRIPTION
		"
		增加了统计量
		rcOptUdEthIfStatisticInPkts         以太网接收包统计,
		rcOptUdEthIfStatisticInPreambleBitErrorPkts         前导码错误包统计,
		rcOptUdEthIfStatisticInFCSErrorPkts         FCS校验错误包统计,
		rcOptUdEthIfStatisticInUndersizePkts         超短包错误统计,
		rcOptUdEthIfStatisticInOversizePkts         超长包错误统计,
		rcOptUdEthIfStatisticInPausePkts         接收PAUSE帧统计,
		rcOptUdEthIfStatisticInOAMPkts         接收OAM帧统计,
		rcOptUdEthIfStatisticOutPkts         以太网发送包统计,
		rcOptUdEthIfStatisticOutFCSErrorPkts         解帧以太网FCS错误帧,
		rcOptUdEthIfStatisticOutPausePkts         发送PAUSE帧统计,
		rcOptUdEthIfStatisticOutOAMPkts         发送OAM帧统计

		在rcOptUdEthInterfaceStatus中，添加了2个bit的定义，定义为端口关闭原因
		"

        REVISION      "1005050000Z"
        DESCRIPTION
            "
            1、add rcOptUdEthInterfaceErrorStatsThreshold
            2、增加rcOptUdEthInterfaceType的枚举3-7.
            3、rcOptUdEthInterfaceStatus
            	bit16:combo接口的实际工作接口类型	1:光口，0：电口

               都是从ethif mib表兼容过来。
               --by huxuehai"

		REVISION      "1006180000Z"
		DESCRIPTION
		"
		增加 rcOptUdEthIfStatisticTimeStamp  流量统计上报时间戳
						----by wuyanxiong
		"
		REVISION      "1006280000Z"
		DESCRIPTION
		"
			1、增加 rcOptUdEthInterfaceFaultPass  故障转移功能设置
				rcOptUdEthInterfaceOutSelect	以太网出口选择
			2、增加rcOptUdEthInterfaceStatus bit定义：
				Bit17:故障转移状态 1：使能，0：禁止
					----by wuyanxiong
		"
 		REVISION      "1007300000Z"
		DESCRIPTION
		"
			1、去掉rcOptUdEthInterfaceOutSelect	以太网出口选择
					----by wuyanxiong
		"
 		REVISION      "1009100000Z"
		DESCRIPTION
		"
			1、增加	rcOptUdEthInterfaceStatus bit位定义
			Bit18:故障转移关闭原因 （bit15-14 = 01时有效）0：因本端其他端口故障转移关，1：因对端端口故障转移关
							----by wuyanxiong
		"
 		REVISION      "1009140000Z"
		DESCRIPTION
		"
			1、增加	rcOptUdEthInterfaceBandwidthStep
				带宽粒度
										----by wuyanxiong
		"

		REVISION      "201009270000Z"
        DESCRIPTION
              "
			  1. 解决ethif与udethif中rcOptUdEthInterfaceStatus节点冲突，
			  	为了与Ethif对齐，保留bit20 bit19，增加bit21:接收到错误报文数超过门限阈值告警状态
			 ----by leishenghua"

 		REVISION      "1012020000Z"
		DESCRIPTION
		"
			1、把带宽粒度rcOptUdEthInterfaceBandwidthStep
			改为接收带宽颗粒度 rcOptUdEthInterfaceRxBandwidthStep
			2、同时增加发送带宽颗粒度 rcOptUdEthInterfaceTxBandwidthStep

									----by wuyanxiong
		"
		REVISION      "1101040000Z"
		DESCRIPTION
		"
			rcOptUdEthIfStatisticInOctets       Integer32-->  Counter64
			rcOptUdEthIfStatisticOutOctets      Integer32-->  Counter64
										----by kuanglili
		"
		REVISION      "1106300000Z"
		DESCRIPTION
		"
			1、增加rcOptUdEthInterfaceStatus bit定义：
				Bit22:光口发送使能状态 1：使能，0：禁止
			2、增加 rcOptUdEthInterfaceTxdisable  光口发送使能设置

									----by hejuan
		"

		REVISION      "1109280000Z"
		DESCRIPTION
		"
			1、增加 rcOptUdEthInterfaceRcLinkdisable  RcLink功能使能设置

									----by liufei
		"
        REVISION      "1206010000Z"
		DESCRIPTION
		"
			1 增加rcOptUdEthInterfacePad 最小长度填充设置
									----by yz
		"

		REVISION      "1205160000Z"
		DESCRIPTION
		"
			1、增加 rcOptUdEthInterfacePhymode        Phy芯片模式设置

									----by liufei
		"
 		REVISION      "1307090000Z"
		DESCRIPTION
		"
			1、增加	rcOptUdEthInterfaceStatus bit位定义
			-- bit27:以太网mac环回状态 1:环回		0:无环回
			-- bit26:以太网phy环回状态 1:环回		0:无环回
			-- bit25:远端收发器掉电告警状态 1: 告警  	0:正常
			-- bit24:phy模式 1：serdes，0：sgmii
			-- bit23:RcLink使能状态 1：使能，0：禁止
			2、增加以太网接口命令rcOptUdEthInterfaceAdminCmd bit位定义
			-- bit2：端口phy环回命令：1：使能环回，0：禁止
			-- bit3：端口mac环回命令：1：使能环回，0：禁止
                    				----by zhuyufeng
		"

        ::= { optUdSysMgmt 20 }



--对象定义
    rcOptUdEthInterfaceObjects       	OBJECT IDENTIFIER ::= { raisecomOptUdEthInterfaceMib 1 }
	rcOptUdEthNotifications      		OBJECT IDENTIFIER ::= { raisecomOptUdEthInterfaceMib 2 }


-- ------------------------------------------------------------
-- 以太网接口物理层接口配置
-- ------------------------------------------------------------

    rcOptUdEthInterfaceTable OBJECT-TYPE
        SYNTAX SEQUENCE OF RcOptUdEthInterfaceEntry
        MAX-ACCESS not-accessible
        STATUS current
         DESCRIPTION
          " The table holding information related to the interface module status."
       ::= { rcOptUdEthInterfaceObjects 1 }

    rcOptUdEthInterfaceEntry OBJECT-TYPE
        SYNTAX  RcOptUdEthInterfaceEntry
        MAX-ACCESS not-accessible
        STATUS current
        DESCRIPTION
        "
        "
        INDEX {rcEntPhysicalID, ifIndex }
        ::= { rcOptUdEthInterfaceTable 1 }

    RcOptUdEthInterfaceEntry ::= SEQUENCE {
        rcOptUdEthInterfaceId
        	Integer32,
        rcOptUdEthInterfaceDescr
            DisplayString,
        rcOptUdEthInterfaceAttribute
        	INTEGER,
        rcOptUdEthInterfaceType
        	INTEGER,
        rcOptUdEthInterfaceStatus
          	Integer32,
        rcOptUdEthInterfaceAutoMdi
          	INTEGER,
		rcOptUdEthInterfaceAutoNego
          	INTEGER,
		rcOptUdEthInterfaceFlowControl
          	INTEGER,
		rcOptUdEthInterfaceAdminCmd
          	Integer32,
		rcOptUdEthInterfaceSpeed
          	INTEGER,
		rcOptUdEthInterfaceDuplex
          	INTEGER,
        rcOptUdEthInterfaceMaxFrameLen
          	INTEGER,
        rcOptUdEthInterfaceALS
          	INTEGER,
        rcOptUdEthInterfaceMaxFrameLength
          	INTEGER,
        rcOptUdEthInterfaceBandwidth
          	Integer32,
        rcOptUdEthInterfaceBandwidthStatus
          	Integer32,
        rcOptUdEthInterfaceCheckLoopback
            INTEGER,
        rcOptUdEthInterfaceCheckLoopbackStatus
          	OCTET STRING (SIZE (16)),
        rcOptUdEthInterfaceModuleType
          	RcOptIfModuleType,
        rcOptUdEthInterfaceRxBandwidth
          	Integer32,
        rcOptUdEthInterfaceRxBandwidthStatus
          	Integer32,
		rcOptUdEthInterfaceTxBandwidth
          	Integer32,
        rcOptUdEthInterfaceTxBandwidthStatus
          	Integer32,
        rcOptUdEthInterfaceErrorStatsThreshold
        	Integer32,
		rcOptUdEthInterfaceFaultPass
			INTEGER,
		rcOptUdEthInterfaceRxBandwidthStep
			INTEGER,
		rcOptUdEthInterfaceTxBandwidthStep
			INTEGER,
		rcOptUdEthInterfaceTxdisable
			INTEGER,
		rcOptUdEthInterfaceRcLinkdisable
			INTEGER,
		rcOptUdEthInterfacePad
            INTEGER,
		rcOptUdEthInterfacePhymode
			INTEGER
    }

    rcOptUdEthInterfaceId OBJECT-TYPE
        SYNTAX  Integer32
        MAX-ACCESS read-only
        STATUS    current
        DESCRIPTION
        "
        -- 接口ID, 第一个接口Id为1,依次类推
        "
        ::={ rcOptUdEthInterfaceEntry 1 }

    rcOptUdEthInterfaceDescr OBJECT-TYPE
        SYNTAX  DisplayString
        MAX-ACCESS read-only
        STATUS    current
        DESCRIPTION
        "
        -- 接口描述
        "
        ::={ rcOptUdEthInterfaceEntry 2 }

    rcOptUdEthInterfaceAttribute OBJECT-TYPE
        SYNTAX  INTEGER
		{
		   	outertrans(1),
		   	outeresw(2),
		   	innertrans(3),
		   	inneresw(4),
		   	switchableesw(5)
		}

        MAX-ACCESS read-only
        STATUS    current
        DESCRIPTION
        "
        -- 接口属性  1:外部传输业务网口，暴露在面板上的，传输业务以太网接口，例如EOS单盘的以太网口
                     2:外部以太网交换网口，暴露在面板上的，可以进行以太网交换相关配置的太网接口，例如交换盘的GE口
                     3:内部传输业务网口，没有暴露在面板上的，传输业务以太网接口，例如rc956上协转FPGA上的以太网口
                     4:内部以太网交换网口，没有暴露在面板上的，可以进行以太网交换相关配置的太网接口，例如rc956交换芯片上与e1相对的以太网口
        	     	 5:可以倒换的以太网交换网口，例如rc956上可以倒换到外部的网口，它的当前状态可以通过rcOptUdEthInterfaceStatus的0比特获得
        "
        ::={ rcOptUdEthInterfaceEntry 3 }

    rcOptUdEthInterfaceType OBJECT-TYPE
        SYNTAX  INTEGER
		{
		   	electrical(1),
		   	optical(2),
		   	electrical100M(3),
		   	optical100M(4),
		   	electrical1000M(5),
		   	optical1000M(6),
		   	combo(7)
		}

        MAX-ACCESS read-only
        STATUS    current
        DESCRIPTION
        "
        -- 接口类型  1:电口
                     2:光口
                     3:百兆电口
                     4:百兆光口
                     5:千兆电口
                     6:千兆光口
                     7:combo口
        "
        ::={ rcOptUdEthInterfaceEntry 4 }

  	rcOptUdEthInterfaceStatus OBJECT-TYPE
		SYNTAX Integer32
		MAX-ACCESS read-only
		STATUS current
		DESCRIPTION
		"
		-- eth接口的状态；
		-- bit27:以太网mac环回状态 1:环回		0:无环回
		-- bit26:以太网phy环回状态 1:环回		0:无环回
		-- bit25:远端收发器掉电告警状态 1: 告警  	0:正常
		-- bit24:phy模式 1：serdes，0：sgmii
		-- bit23:RcLink使能状态 1：使能，0：禁止
		-- bit22:光口发送使能状态:	1:使能		0:禁止
		-- bit21:接收到错误报文数超过门限阈值告警状态：  	1：越限，        0：没有越限
		-- bit20:保留，不推荐使用
		   bit19:保留，不推荐使用
		-- Bit18:故障转移关闭原因 （bit15-14 = 01时有效）0：因本端其他端口故障转移关，1：因对端端口故障转移关
		-- bit17:故障转移状态 1：使能，0：禁止
		-- bit16:combo接口的实际工作接口类型	1:光口，0：电口
		-- bit15:端口关闭原因(bit4=0时有效)：  	00：因网管命令关，  01：因故障转移关
		   bit14:		                		10：因ALS关，  		11：因检测到环回关
		-- bit13:自适应工作状态：  	1：成功，        0：失败
		-- bit12:energy：	1：无能量，光纤或电缆尚未连接        0：有能量，光纤或电缆已经连接（目前只有交换盘关心这个bit）
		-- bit11:ALS：		1：使能，        0：禁止
		-- bit10:接口状态：	1：交叉，	 0：直连
		-- bit9:自适应状态：  	1：使能，        0：禁止
		-- bit8:流控状态：    	1：使能，        0：禁止
		-- bit7:光口tlink状态：	1：Link up       0：Link Down
		-- bit6:光口rlink状态：	1：Link up       0：Link Down
		-- bit5:电口连接状态：	1：Link up       0：Link Down
		-- bit4:端口状态：    	1：使能          0：禁止/关闭
		-- bit3
		   bit2:连接速度： 	11:1000M   	 10：100M          01：10M
		-- bit1:双工状态：    	1：全双工        0：半双工
		-- bit0:以太口的位置  	0：出口在前面板	 1：出口到背板
		"
		::= { rcOptUdEthInterfaceEntry 5 }

  	rcOptUdEthInterfaceAutoMdi OBJECT-TYPE
		SYNTAX INTEGER
		{
			enable(1),
			disable(2)
		}
		MAX-ACCESS read-write
		STATUS current
		DESCRIPTION
		"
		-- eth接口自动交叉功能：（1：使能，2：禁止）
		"
		::= { rcOptUdEthInterfaceEntry 6 }

  	rcOptUdEthInterfaceAutoNego OBJECT-TYPE
		SYNTAX INTEGER
		{
			enable(1),
			disable(2)
		}
		MAX-ACCESS read-write
		STATUS current
		DESCRIPTION
		"
		-- eth接口自适应功能:（1：使能，2：禁止）
		"
		::= { rcOptUdEthInterfaceEntry 7 }

  	rcOptUdEthInterfaceFlowControl OBJECT-TYPE
		SYNTAX INTEGER
		{
			on(1),
			off(2)
		}
		MAX-ACCESS read-write
		STATUS current
		DESCRIPTION
		"
		-- eth接口的流控功能:（1：打开，2：关闭）
		"
		::= { rcOptUdEthInterfaceEntry 8 }

  	rcOptUdEthInterfaceAdminCmd OBJECT-TYPE
		SYNTAX Integer32
		MAX-ACCESS read-write
		STATUS current
		DESCRIPTION
		"
		-- eth接口的端口管理状态:
			-- bit0: 端口管理状态：1：使能，0：禁止
			-- bit1：端口统计命令：1：清空当前报文统计信息
			-- bit2：端口phy环回命令：1：使能环回，0：禁止
			-- bit3：端口mac环回命令：1：使能环回，0：禁止
		"
		::= { rcOptUdEthInterfaceEntry 9 }

  	rcOptUdEthInterfaceSpeed OBJECT-TYPE
		SYNTAX INTEGER
		{
			speed10M(1),
			speed100M(2),
			speed1000M(3)
		}
		MAX-ACCESS read-write
		STATUS current
		DESCRIPTION
		"
		-- eth接口的速率：（1：10M，2：100M,3:1000M）
		"
		::= { rcOptUdEthInterfaceEntry 10 }

  	rcOptUdEthInterfaceDuplex OBJECT-TYPE
		SYNTAX INTEGER
        {
            full-duplex(1),
            half-duplex(2)
        }
		MAX-ACCESS read-write
		STATUS current
		DESCRIPTION
		"
		-- eth接口双工状态:(1：全双工,2：半双工)
		"
		::= { rcOptUdEthInterfaceEntry 11 }

  	rcOptUdEthInterfaceMaxFrameLen OBJECT-TYPE
		SYNTAX INTEGER
        {
            length1916(1),
            length1536(2),
            length1632(3)
        }
		MAX-ACCESS read-write
		STATUS current
		DESCRIPTION
		"
		-- 最大帧长：（1:1916字节，2：1536字节,3:1632字节）
		"
		::= { rcOptUdEthInterfaceEntry 12 }

	 rcOptUdEthInterfaceALS OBJECT-TYPE
		SYNTAX INTEGER
        {
            enable(1),
            disable(2)
        }
		MAX-ACCESS read-write
		STATUS current
		DESCRIPTION
		"
		-- 自动激光器关断：（1:enable，2：disable）
		"
		::= { rcOptUdEthInterfaceEntry 13 }

  	rcOptUdEthInterfaceMaxFrameLength OBJECT-TYPE
		SYNTAX  INTEGER(64..12000)
		MAX-ACCESS read-write
		STATUS current
		DESCRIPTION
		"
		-- 最大帧长的字节数
		"
		::= { rcOptUdEthInterfaceEntry 14 }

    rcOptUdEthInterfaceBandwidth OBJECT-TYPE
        SYNTAX  Integer32
        MAX-ACCESS read-write
        STATUS    current
        DESCRIPTION
        "
            -- 端口带宽设置：使用的时隙个数  (0~32)
        "
        ::={ rcOptUdEthInterfaceEntry 15 }
    rcOptUdEthInterfaceBandwidthStatus OBJECT-TYPE
        SYNTAX  Integer32
        MAX-ACCESS read-only
        STATUS    current
        DESCRIPTION
        "
            -- 端口带宽状态：使用的时隙个数  (0~32)
        "
        ::={ rcOptUdEthInterfaceEntry 16 }
	rcOptUdEthInterfaceCheckLoopback OBJECT-TYPE
		SYNTAX INTEGER
		{
			enable(1),
			disable(2)
		}
		MAX-ACCESS read-write
		STATUS current
		DESCRIPTION
		"
		-- eth接口环回检测功能设置:（1：使能，2：禁止）
		"
		::= { rcOptUdEthInterfaceEntry 17 }

	rcOptUdEthInterfaceCheckLoopbackStatus OBJECT-TYPE
		SYNTAX OCTET STRING (SIZE (16))
		MAX-ACCESS read-only
		STATUS current
		DESCRIPTION
		"
			--eth接口环回检测状态: 字符串表示环回对应端口的比特位表,
			  比特0表示端口1 ...
			  （1:有环回，0:无环回），可能有多个端口与本端口发生环回
			  每一个比特标识一个端口，每一个字节代表8个端口，最多支持128个端口相关的环回。
		"
		::= { rcOptUdEthInterfaceEntry 18 }

    rcOptUdEthInterfaceModuleType OBJECT-TYPE
        SYNTAX  RcOptIfModuleType
        MAX-ACCESS read-only
        STATUS    current
        DESCRIPTION
        "
            -- 光接口模块类型
        "
        ::={ rcOptUdEthInterfaceEntry 19 }

    rcOptUdEthInterfaceRxBandwidth OBJECT-TYPE
        SYNTAX  Integer32
        MAX-ACCESS read-write
        STATUS    current
        DESCRIPTION
        "
            -- 端口接收带宽设置：
                -- 数值范围(1~0x061A)，带宽为本数值*64K，即带宽范围（64K~100M）

			注：本对象节点目前只用于rc3000-15-(P)480fe和rc3000-15-(P)240fe
        "
        ::={ rcOptUdEthInterfaceEntry 20 }
    rcOptUdEthInterfaceRxBandwidthStatus OBJECT-TYPE
        SYNTAX  Integer32
        MAX-ACCESS read-only
        STATUS    current
        DESCRIPTION
        "
            -- 端口接收带宽设置状态：
            -- 数值范围(1~0x061A)，带宽为本数值*64K，即带宽范围（64K~100M）

			注：本对象节点目前只用于rc3000-15-(P)480fe和rc3000-15-(P)240fe
        "
        ::={ rcOptUdEthInterfaceEntry 21 }
	rcOptUdEthInterfaceTxBandwidth OBJECT-TYPE
        SYNTAX  Integer32
        MAX-ACCESS read-write
        STATUS    current
        DESCRIPTION
        "
            -- 端口发送带宽设置：
            -- 数值范围(1~0x061A)，带宽为本数值*64K，即带宽范围（64K~100M）

			注：本对象节点目前只用于rc3000-15-(P)480fe和rc3000-15-(P)240fe
        "
        ::={ rcOptUdEthInterfaceEntry 22 }
    rcOptUdEthInterfaceTxBandwidthStatus OBJECT-TYPE
        SYNTAX  Integer32
        MAX-ACCESS read-only
        STATUS    current
        DESCRIPTION
        "
            -- 端口发送带宽设置状态：
            -- 数值范围(1~0x061A)，带宽为本数值*64K，即带宽范围（64K~100M）

			注：本对象节点目前只用于rc3000-15-(P)480fe和rc3000-15-(P)240fe
        "
        ::={ rcOptUdEthInterfaceEntry 23 }

    rcOptUdEthInterfaceErrorStatsThreshold OBJECT-TYPE
        SYNTAX  Integer32 (1..2147483647)
        MAX-ACCESS read-write
        STATUS    current
        DESCRIPTION
        "
            -- 以太网接口错误统计阈值，错误统计计数超过阈值上报告警，
            -- 统计计数清零告警恢复。

			注：本对象节点目前只用于4EOS4FE，因为只有这个板卡可以统计到接受CRC错误报文。
			该节点增加只是为了满足CNC MSAP测试，可能将来不会正式使用。
        "
        DEFVAL { 65535 }
        ::={ rcOptUdEthInterfaceEntry 24 }

	rcOptUdEthInterfaceFaultPass OBJECT-TYPE
        SYNTAX INTEGER
		{
			enable(1),
			disable(2)
		}
        MAX-ACCESS read-write
        STATUS    current
        DESCRIPTION
        "
			-- 故障转移功能设置
				1:使能	2:禁止
        "
        ::={ rcOptUdEthInterfaceEntry 25 }

	rcOptUdEthInterfaceRxBandwidthStep OBJECT-TYPE
        SYNTAX INTEGER
		{
			step64Kbps(1),
			step32Kbps(2),
			step80Kbps(3),
			step800Kbps(4),
			step8000Kbps(5)
		}
        MAX-ACCESS read-only
        STATUS    current
        DESCRIPTION
        "
			接收带宽粒度:
			1：64Kbps；
			2：32Kbps；
			3：80Kbps;
			4：800Kbps;
			5：8000Kbps;
			其余：保留。

        "
        ::={ rcOptUdEthInterfaceEntry 26 }

	rcOptUdEthInterfaceTxBandwidthStep OBJECT-TYPE
        SYNTAX INTEGER
		{
			step64Kbps(1),
			step32Kbps(2),
			step80Kbps(3),
			step800Kbps(4),
			step8000Kbps(5)
		}
        MAX-ACCESS read-only
        STATUS    current
        DESCRIPTION
        "
			发送带宽粒度:
			1：64Kbps；
			2：32Kbps；
			3：80Kbps;
			4：800Kbps;
			5：8000Kbps;
			其余：保留。

        "
        ::={ rcOptUdEthInterfaceEntry 27 }

 	rcOptUdEthInterfaceTxdisable OBJECT-TYPE
        SYNTAX INTEGER
		{
			enable(1),
			disable(2)
		}
        MAX-ACCESS read-write
        STATUS    current
        DESCRIPTION
        "
			-- 光口发送使能设置
				1:使能	2:禁止
        "
        ::={ rcOptUdEthInterfaceEntry 28 }

 	rcOptUdEthInterfaceRcLinkdisable OBJECT-TYPE
        SYNTAX INTEGER
		{
			enable(1),
			disable(2)
		}
        MAX-ACCESS read-write
        STATUS    current
        DESCRIPTION
        "
			-- RcLink使能设置
				1:使能	2:禁止
        "
        ::={ rcOptUdEthInterfaceEntry 29 }
    rcOptUdEthInterfacePad OBJECT-TYPE
           SYNTAX INTEGER
           {
               enable(1),
               disable(2)
           }
           MAX-ACCESS  read-write
           STATUS      current
           DESCRIPTION
           	"
                -- 最小长度填充并生成FCS
            "
           DEFVAL { disable }
        ::= { rcOptUdEthInterfaceEntry 30 }
 	rcOptUdEthInterfacePhymode OBJECT-TYPE
        SYNTAX INTEGER
		{
			serdes(1),
			sgmii(2)
		}
        MAX-ACCESS read-write
        STATUS    current
        DESCRIPTION
        "
			-- Phy芯片模式设置
				1:serdes模式 2:sgmii模式
        "
        ::={ rcOptUdEthInterfaceEntry 31 }


-- ------------------------------------------------------------
-- 以太网接口物理层接口统计信息
-- ------------------------------------------------------------

    rcOptUdEthIfStatisticTable OBJECT-TYPE
        SYNTAX SEQUENCE OF RcOptUdEthIfStatisticEntry
        MAX-ACCESS not-accessible
        STATUS current
         DESCRIPTION
          "The table holding information related to the interface module status."
       ::= { rcOptUdEthInterfaceObjects 2 }

    rcOptUdEthIfStatisticEntry OBJECT-TYPE
        SYNTAX  RcOptUdEthIfStatisticEntry
        MAX-ACCESS not-accessible
        STATUS current
        DESCRIPTION
        "
        "
        INDEX {rcEntPhysicalID, ifIndex }
        ::= { rcOptUdEthIfStatisticTable 1 }

    RcOptUdEthIfStatisticEntry ::= SEQUENCE {
        rcOptUdEthIfStatisticInOctets
        	Counter64,
        rcOptUdEthIfStatisticInUnicastPkts
        	Integer32,
        rcOptUdEthIfStatisticInMulticastPkts
        	Integer32,
        rcOptUdEthIfStatisticInBroadcastPkts
        	Integer32,
        rcOptUdEthIfStatisticInDiscardPkts
        	Integer32,
        rcOptUdEthIfStatisticInErrorPkts
        	Integer32,
        rcOptUdEthIfStatisticOutOctets
        	Counter64,
        rcOptUdEthIfStatisticOutUnicastPkts
        	Integer32,
        rcOptUdEthIfStatisticOutMulticastPkts
        	Integer32,
        rcOptUdEthIfStatisticOutBroadcastPkts
        	Integer32,
        rcOptUdEthIfStatisticOutDiscardPkts
        	Integer32,
        rcOptUdEthIfStatisticOutErrorPkts
        	Integer32,

		rcOptUdEthIfStatisticInPkts         Integer32,
		rcOptUdEthIfStatisticInPreambleBitErrorPkts         Integer32,
		rcOptUdEthIfStatisticInFCSErrorPkts         Integer32,
		rcOptUdEthIfStatisticInUndersizePkts         Integer32,
		rcOptUdEthIfStatisticInOversizePkts         Integer32,
		rcOptUdEthIfStatisticInPausePkts         Integer32,
		rcOptUdEthIfStatisticInOAMPkts         Integer32,
		rcOptUdEthIfStatisticOutPkts         Integer32,
		rcOptUdEthIfStatisticOutFCSErrorPkts         Integer32,
		rcOptUdEthIfStatisticOutPausePkts         Integer32,
		rcOptUdEthIfStatisticOutOAMPkts         Integer32,

		rcOptUdEthIfStatisticTimeStamp
			Integer32
    }

    rcOptUdEthIfStatisticInOctets OBJECT-TYPE
        SYNTAX  Counter64
        MAX-ACCESS read-only
        STATUS    current
        DESCRIPTION
        "输入有效字节数"
        ::={ rcOptUdEthIfStatisticEntry 1 }

    rcOptUdEthIfStatisticInUnicastPkts OBJECT-TYPE
        SYNTAX  Integer32
        MAX-ACCESS read-only
        STATUS    current
        DESCRIPTION
        "
        	输入单播包数
        "
        ::={ rcOptUdEthIfStatisticEntry 2 }

    rcOptUdEthIfStatisticInMulticastPkts OBJECT-TYPE
        SYNTAX  Integer32
        MAX-ACCESS read-only
        STATUS    current
        DESCRIPTION
        "
        	输入多播包数
        "
        ::={ rcOptUdEthIfStatisticEntry 3 }

    rcOptUdEthIfStatisticInBroadcastPkts OBJECT-TYPE
        SYNTAX  Integer32
        MAX-ACCESS read-only
        STATUS    current
        DESCRIPTION
        "
        	输入广播包数目
        "
        ::={ rcOptUdEthIfStatisticEntry 4 }

    rcOptUdEthIfStatisticInDiscardPkts OBJECT-TYPE
        SYNTAX  Integer32
        MAX-ACCESS read-only
        STATUS    current
        DESCRIPTION
        "
        	输入丢弃包数目
        "
        ::={ rcOptUdEthIfStatisticEntry 5 }

    rcOptUdEthIfStatisticInErrorPkts OBJECT-TYPE
        SYNTAX  Integer32
        MAX-ACCESS read-only
        STATUS    current
        DESCRIPTION
        "
        	输入的错误包数目
        "
        ::={ rcOptUdEthIfStatisticEntry 6 }

    rcOptUdEthIfStatisticOutOctets OBJECT-TYPE
        SYNTAX  Counter64
        MAX-ACCESS read-only
        STATUS    current
        DESCRIPTION
        "
        	输出的有效字节数
        "
        ::={ rcOptUdEthIfStatisticEntry 7 }

    rcOptUdEthIfStatisticOutUnicastPkts OBJECT-TYPE
        SYNTAX  Integer32
        MAX-ACCESS read-only
        STATUS    current
        DESCRIPTION
        "
        	输出单播包数目
        "
        ::={ rcOptUdEthIfStatisticEntry 8 }

    rcOptUdEthIfStatisticOutMulticastPkts OBJECT-TYPE
        SYNTAX  Integer32
        MAX-ACCESS read-only
        STATUS    current
        DESCRIPTION
        "
        	输出多播包数目
        "
        ::={ rcOptUdEthIfStatisticEntry 9 }

    rcOptUdEthIfStatisticOutBroadcastPkts OBJECT-TYPE
        SYNTAX  Integer32
        MAX-ACCESS read-only
        STATUS    current
        DESCRIPTION
        "
        	输出广播包数目
        "
        ::={ rcOptUdEthIfStatisticEntry 10 }

    rcOptUdEthIfStatisticOutDiscardPkts OBJECT-TYPE
        SYNTAX  Integer32
        MAX-ACCESS read-only
        STATUS    current
        DESCRIPTION
        "
        	输出丢弃包数目
        "
        ::={ rcOptUdEthIfStatisticEntry 11 }

    rcOptUdEthIfStatisticOutErrorPkts OBJECT-TYPE
        SYNTAX  Integer32
        MAX-ACCESS read-only
        STATUS    current
        DESCRIPTION
        "
        	输出错误包数目
        "
        ::={ rcOptUdEthIfStatisticEntry 12 }


			rcOptUdEthIfStatisticInPkts OBJECT-TYPE
					SYNTAX Integer32
					MAX-ACCESS read-only
					STATUS current
					DESCRIPTION
					"
						以太网接收包统计
					"
					::= { rcOptUdEthIfStatisticEntry 13 }

	 		rcOptUdEthIfStatisticInPreambleBitErrorPkts OBJECT-TYPE
					SYNTAX Integer32
					MAX-ACCESS read-only
					STATUS current
					DESCRIPTION
						"
							前导码错误包统计
						"
					::= { rcOptUdEthIfStatisticEntry 14 }

	 		rcOptUdEthIfStatisticInFCSErrorPkts OBJECT-TYPE
					SYNTAX Integer32
					MAX-ACCESS read-only
					STATUS current
					DESCRIPTION
						"
							FCS校验错误包统计
						"
					::= { rcOptUdEthIfStatisticEntry 15 }

	 		rcOptUdEthIfStatisticInUndersizePkts OBJECT-TYPE
					SYNTAX Integer32
					MAX-ACCESS read-only
					STATUS current
					DESCRIPTION
						"
							超短包错误统计
						"
					::= { rcOptUdEthIfStatisticEntry 16 }

	 		rcOptUdEthIfStatisticInOversizePkts OBJECT-TYPE
					SYNTAX Integer32
					MAX-ACCESS read-only
					STATUS current
					DESCRIPTION
						"
							超长包错误统计
						"
					::= { rcOptUdEthIfStatisticEntry 17 }

	 		rcOptUdEthIfStatisticInPausePkts OBJECT-TYPE
					SYNTAX Integer32
					MAX-ACCESS read-only
					STATUS current
					DESCRIPTION
						"
							接收PAUSE帧统计
						"
					::= { rcOptUdEthIfStatisticEntry 18 }

	 		rcOptUdEthIfStatisticInOAMPkts OBJECT-TYPE
					SYNTAX Integer32
					MAX-ACCESS read-only
					STATUS current
					DESCRIPTION
						"
							 接收OAM帧统计
						"
					::= { rcOptUdEthIfStatisticEntry 19 }

	 		rcOptUdEthIfStatisticOutPkts OBJECT-TYPE
					SYNTAX Integer32
					MAX-ACCESS read-only
					STATUS current
					DESCRIPTION
						"
							 以太网发送包统计
						"
					::= { rcOptUdEthIfStatisticEntry 20 }

	 		rcOptUdEthIfStatisticOutFCSErrorPkts OBJECT-TYPE
					SYNTAX Integer32
					MAX-ACCESS read-only
					STATUS current
					DESCRIPTION
						"
							 解帧以太网FCS错误帧
						"
					::= { rcOptUdEthIfStatisticEntry 21 }

	 		rcOptUdEthIfStatisticOutPausePkts OBJECT-TYPE
					SYNTAX Integer32
					MAX-ACCESS read-only
					STATUS current
					DESCRIPTION
						"
							 发送PAUSE帧统计
						"
					::= { rcOptUdEthIfStatisticEntry 22 }

	 		rcOptUdEthIfStatisticOutOAMPkts OBJECT-TYPE
					SYNTAX Integer32
					MAX-ACCESS read-only
					STATUS current
					DESCRIPTION
						"
							 发送OAM帧统计
						"
					::= { rcOptUdEthIfStatisticEntry 23 }

	 		rcOptUdEthIfStatisticTimeStamp OBJECT-TYPE
					SYNTAX Integer32
					MAX-ACCESS read-only
					STATUS current
					DESCRIPTION
						"
							 流量统计上报时间戳
						"
					::= { rcOptUdEthIfStatisticEntry 24 }






-- ------------------------------------------------------
--  告警信息定义
-- ------------------------------------------------------

	rcOptUdEthNotificationPrefix     OBJECT IDENTIFIER ::= { rcOptUdEthNotifications 0 }

	rcOptUdEthTlinkDownTrap NOTIFICATION-TYPE
		OBJECTS { rcNotifsTrapLocation, rcEntPhysicalID, ifIndex }
		STATUS             current
		DESCRIPTION
		"
			Eth tlink down
		"
		::= { rcOptUdEthNotificationPrefix 102701 }

	rcOptUdEthTlinkUpTrap NOTIFICATION-TYPE
		OBJECTS { rcNotifsTrapLocation, rcEntPhysicalID, ifIndex }
		STATUS             current
		DESCRIPTION
		"
			Eth tlink up.
		"
		::= { rcOptUdEthNotificationPrefix 102702 }

	 rcOptUdEthRlinkDownTrap NOTIFICATION-TYPE
		OBJECTS { rcNotifsTrapLocation, rcEntPhysicalID, ifIndex }
		STATUS             current
		DESCRIPTION
		"
			Eth rlink down
		"
		::= { rcOptUdEthNotificationPrefix 102703 }

	rcOptUdEthRlinkUpTrap NOTIFICATION-TYPE
		OBJECTS { rcNotifsTrapLocation, rcEntPhysicalID, ifIndex }
		STATUS             current
		DESCRIPTION
		"
			Eth rlink up.
		"
		::= { rcOptUdEthNotificationPrefix 102704 }


	rcOptUdEthEnergyNotDetectedTrap NOTIFICATION-TYPE
		OBJECTS { rcNotifsTrapLocation, rcEntPhysicalID, ifIndex }
		STATUS             current
		DESCRIPTION
		"
			Eth energy not detected.
		"
		::= { rcOptUdEthNotificationPrefix 102705 }

	rcOptUdEthEnergyDetectedTrap NOTIFICATION-TYPE
		OBJECTS { rcNotifsTrapLocation, rcEntPhysicalID, ifIndex }
		STATUS             current
		DESCRIPTION
		"
			Eth energy detected.
		"
		::= { rcOptUdEthNotificationPrefix 102706 }

	rcOptUdEthlinkDownTrap NOTIFICATION-TYPE
		OBJECTS { rcNotifsTrapLocation, rcEntPhysicalID, ifIndex }
		STATUS             current
		DESCRIPTION
		"
			Eth FE link down.仅远端设备发送
		"
		::= { rcOptUdEthNotificationPrefix 102707 }

	rcOptUdEthlinkUpTrap NOTIFICATION-TYPE
		OBJECTS { rcNotifsTrapLocation, rcEntPhysicalID, ifIndex }
		STATUS             current
		DESCRIPTION
		"
			Eth FE link up.仅远端设备发送
		"
		::= { rcOptUdEthNotificationPrefix 102708 }
END
