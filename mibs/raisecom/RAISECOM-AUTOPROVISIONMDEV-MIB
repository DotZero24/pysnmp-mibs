-- MibName=raisecomAutoProvisionMdev
-- *****************************************************************
-- RAISECOM-AUTOPROVISIONMDEV-MIB.mib:	 Raisecom AUOTPRIVISION MIB file
--
-- Sep 2012, liconge
--
-- Copyright (c) 1994-2012,	2012 by	Raisecom, Inc.
-- All rights reserved.
--
--
-- *****************************************************************
RAISECOM-AUTOPROVISIONMDEV-MIB DEFINITIONS ::= BEGIN

IMPORTS
		    iscomSwitch
				    FROM RAISECOM-BASE-MIB
		    MacAddress
				    FROM SNMPv2-TC
        RowStatus
        		FROM SNMPv2-TC
        Ipv6Address
            FROM IPV6-TC
        PortList
            FROM SWITCH-TC
		    Gauge32
				    FROM SNMPv2-SMI;

raisecomAutoProvisionMdev MODULE-IDENTITY
		LAST-UPDATED	"201209130000Z"
		ORGANIZATION	"Raisecom, Inc."
		CONTACT-INFO
				"		Raise Systems

				    Postal:	Beijing, China

				       Tel:	86-010-82884499

				    E-mail:	support@raisecom.com"
		DESCRIPTION
				"The MIB module for Auto Provision management device."
				::=	{ iscomSwitch	78 }


-- -------------------------------------------------------------------------- --
-- define groups in RAISECOM-AUOTPRIVISION-MIB
-- ----------------------------------------------------------------------------
	-- raisecomAutoProvisionMgtTable		      OBJECT IDENTIFIER ::= {	raisecomAutoProvision 1 }
	-- raisecomAutoProvisionRemoteTable		  OBJECT IDENTIFIER ::= {	raisecomAutoProvision 2 }
	-- raisecomAutoProvisionClientInfo	      OBJECT IDENTIFIER ::= {	raisecomAutoProvision 3 }
-- ----------------------------------------------------------------------------

	-- START raisecomAutoProvisionMgtTable--

	raisecomAutoProvisionMgtTable             OBJECT-TYPE
		SYNTAX		SEQUENCE OF	raisecomAutoProvisionMgtEntry
		MAX-ACCESS	not-accessible
		STATUS		current
		DESCRIPTION
			"A table of	ip interface."
		::=	{ raisecomAutoProvisionMdev 1}

	raisecomAutoProvisionMgtEntry              OBJECT-TYPE
		SYNTAX		raisecomAutoProvisionMgtEntry
		MAX-ACCESS	not-accessible
		STATUS		current
		DESCRIPTION
			"Table entry for IP interface."
		INDEX {	raisecomAutoProvisionIPInterfaceIndex  }
		::=	{ raisecomAutoProvisionMgtTable 1 }

	raisecomAutoProvisionMgtEntry ::= SEQUENCE {
		raisecomAutoProvisionIPInterfaceIndex					INTEGER	(0..14),
		raisecomAutoProvisionNetworkSegment   				INTEGER (1..254),
		raisecomAutoProvisionPortlist        					PortList,
		raisecomAutoProvisionGenerateARP  			      INTEGER,
		raisecomAutoProvisionSNMPHost    				      IpAddress,
		raisecomAutoProvisionAdvertiseInterval  		  INTEGER	(1..10),
		raisecomAutoProvisionAdvertiseTimes   		    INTEGER(0..10),
		raisecomAutoProvisionAdvertiseOper     			  INTEGER,
		raisecomProvisionCurSequence        	        INTEGER,
		raisecomProvisionSendAdvertises  						  INTEGER,
		raisecomProvisionRcvAcks                      INTEGER,
		raisecomProvisionClearStatistic               INTEGER,
		raisecomProvisionSendTrapEnable               INTEGER,
		raisecomAutoProvisionTFTPServer               IpAddress,
		raisecomAutoProvisionConfigFileNameRule       INTEGER,
		raisecomAutoProvisionConfigFileNamePrefix     OCTET STRING (SIZE(0..16)),
		raisecomAutoProvisionConfigFileNamePostfix    OCTET STRING (SIZE(0..16)),
	}

	raisecomAutoProvisionIPInterfaceIndex     OBJECT-TYPE
		SYNTAX	INTEGER	(0..14)
		ACCESS	not-accessible
		STATUS	current
		DESCRIPTION
			"An index that uniquely identifies an entry in
             the auto provision table."
		::=	{ raisecomAutoProvisionMgtEntry 1 }

	raisecomAutoProvisionNetworkSegment       OBJECT-TYPE
		SYNTAX	INTEGER (1..254)
		ACCESS	read-write
		STATUS	current
		DESCRIPTION
			"Management network segment."
		::=	{ raisecomAutoProvisionMgtEntry 2 }

	raisecomAutoProvisionPortlist             OBJECT-TYPE
		SYNTAX	PortList
		ACCESS	read-write
		STATUS	current
		DESCRIPTION
			"Auto Provision Port List."
		::=	{ raisecomAutoProvisionMgtEntry 3 }

	raisecomAutoProvisionGenerateARP          OBJECT-TYPE
		SYNTAX	INTEGER
		{
			no(0),
		  yes(1)
		}
		ACCESS	read-write
		STATUS	current
		DESCRIPTION
			"This object indicates if generate ARP."
		::=	{ raisecomAutoProvisionMgtEntry 4 }

	raisecomAutoProvisionSNMPHost             OBJECT-TYPE
		SYNTAX	IpAddress
		ACCESS	read-write
		STATUS	current
		DESCRIPTION
			"IP address of SNMP Host."
		::=	{ raisecomAutoProvisionMgtEntry 5 }

	raisecomAutoProvisionAdvertiseInterval    OBJECT-TYPE
		SYNTAX	INTEGER (1..10)
		ACCESS	read-write
		STATUS	current
		DESCRIPTION
			"Interval of send advertise message."
		::=	{ raisecomAutoProvisionMgtEntry 6 }

	raisecomAutoProvisionAdvertiseTimes       OBJECT-TYPE
		SYNTAX	INTEGER
		ACCESS	read-write
		STATUS	current
		DESCRIPTION
			"Times of sending advertise message. The value forever(0) is used to all the time."
		::=	{ raisecomAutoProvisionMgtEntry 7 }

	raisecomAutoProvisionAdvertiseOper        OBJECT-TYPE
		SYNTAX	INTEGER
		{
    	start(1),
    	stop(2),
    	disable(3)
		}
		ACCESS	read-write
		STATUS	current
		DESCRIPTION
			"The value start(1) is used to enable auto function, stop(2) is used to stop auto function, disable(3) is used to disable function."
	   ::= { raisecomAutoProvisionMgtEntry 8	}

	raisecomProvisionCurSequence              OBJECT-TYPE
		SYNTAX	INTEGER
		ACCESS	read-only
		STATUS	current
		DESCRIPTION
			"The sequence ID of Advertise message."
		::=	{ raisecomAutoProvisionMgtEntry 9 }

	raisecomProvisionSendAdvertises           OBJECT-TYPE
		SYNTAX	INTEGER
		ACCESS	read-only
		STATUS	current
		DESCRIPTION
			"This object indicates the advertise message has been sent number."
		::=	{ raisecomAutoProvisionMgtEntry 10 }

	raisecomProvisionRcvAcks                  OBJECT-TYPE
		SYNTAX	INTEGER
		ACCESS	read-only
		STATUS	current
		DESCRIPTION
			"This object indicates the Ack message has been received number."
		::=	{ raisecomAutoProvisionMgtEntry 11 }

	raisecomProvisionClearStatistic           OBJECT-TYPE
		SYNTAX	INTEGER
		{
			clear(1)
		}
		ACCESS	read-write
		STATUS	current
		DESCRIPTION
			"Clear Statistics."
		::=	{ raisecomAutoProvisionMgtEntry 12 }

	raisecomProvisionSendTrapEnable           OBJECT-TYPE
		SYNTAX	INTEGER
		{
			enable(1),
      disable(0)
		}
		ACCESS	read-write
		STATUS	current
		DESCRIPTION
			"The value enable(0)is used to send trap to NM,
			disable(1) is used not to send trap."
		::=	{ raisecomAutoProvisionMgtEntry 13 }

  raisecomAutoProvisionTFTPServer             OBJECT-TYPE
		SYNTAX	IpAddress
		ACCESS	read-write
		STATUS	current
		DESCRIPTION
			"IP address of TFTP server."
		::=	{ raisecomAutoProvisionMgtEntry 14 }

	raisecomAutoProvisionConfigFileNameRule             OBJECT-TYPE
		SYNTAX	INTEGER (80000..89999)
		ACCESS	read-write
		STATUS	current
		DESCRIPTION
			"The filename rule number."
		::=	{ raisecomAutoProvisionMgtEntry 15 }

  raisecomAutoProvisionConfigFileNamePrefix             OBJECT-TYPE
		SYNTAX	OCTET STRING (SIZE(0..16))
		ACCESS	read-write
		STATUS	current
		DESCRIPTION
			"The object indicates the config file name prefix."
		::=	{ raisecomAutoProvisionMgtEntry 16 }

  raisecomAutoProvisionConfigFileNamePostfix             OBJECT-TYPE
		SYNTAX	OCTET STRING (SIZE(0..16))
		ACCESS	read-write
		STATUS	current
		DESCRIPTION
			"IP address of TFTP server."
		::=	{ raisecomAutoProvisionMgtEntry 17 }

	-- END raisecomAutoProvisionMgtTable

	-- START raisecomAutoProvisionRemoteTable

	raisecomAutoProvisionRemoteTable          OBJECT-TYPE
		SYNTAX		  SEQUENCE OF raisecomAutoProvisionRemoteEntry
		MAX-ACCESS	not-accessible
		STATUS		  current
		DESCRIPTION
			"The value of the remote device MAC address."
		::=	{ raisecomAutoProvisionMdev 2	}

	raisecomAutoProvisionRemoteEntry          OBJECT-TYPE
		SYNTAX		  raisecomAutoProvisionRemoteEntry
		MAX-ACCESS	not-accessible
		STATUS		  current
		DESCRIPTION
			"Table entry for mac and status	information."
		INDEX {	raisecomAutoProvisionRemoteMac }
		::=	{ raisecomAutoProvisionRemoteTable	1 }

	raisecomAutoProvisionRemoteEntry ::= SEQUENCE {
			raisecomAutoProvisionRemoteMac				        MacAddress,
			raisecomAutoProvisionRemoteDelInfo  		      INTEGER,
			raisecomAutoProvisionRemoteIPinterface        INTEGER (0..14),
			raisecomAutoProvisionRemoteType       			  OCTET STRING (SIZE(1..64)),
			raisecomAutoProvisionRemotePort  						  INTEGER (1..24),
			raisecomAutoProvisionRemoteSysOID  		        OCTET STRING (SIZE(1..64)),
			raisecomAutoProvisionRemoteStatus   	 			  INTEGER,
			raisecomAutoProvisionRemoteVid     	     		  INTEGER (1..4094),
}

	raisecomAutoProvisionRemoteMac            OBJECT-TYPE
		SYNTAX	MacAddress
		ACCESS	not-accessible
		STATUS	current
		DESCRIPTION
			"The value of the remote device MAC address."
		::=	{ raisecomAutoProvisionRemoteEntry	1 }

	raisecomAutoProvisionRemoteDelInfo        OBJECT-TYPE
		SYNTAX	INTEGER
						{
              del(1)
            }
		ACCESS	read-write
		STATUS	current
		DESCRIPTION
			"The value of the remote device MAC address."
		::=	{ raisecomAutoProvisionRemoteEntry	2 }

	raisecomAutoProvisionRemoteIPinterface    OBJECT-TYPE
		SYNTAX	INTEGER (0..14)
		ACCESS	read-only
		STATUS	current
		DESCRIPTION
			"IP interface of remote device."
		::=	{ raisecomAutoProvisionRemoteEntry	3 }

	raisecomAutoProvisionRemoteType           OBJECT-TYPE
		SYNTAX	OCTET STRING (SIZE(1..64))
		ACCESS	read-only
		STATUS	current
		DESCRIPTION
			"Remote device type ."
		::=	{ raisecomAutoProvisionRemoteEntry	4 }

  raisecomAutoProvisionRemotePort           OBJECT-TYPE
		SYNTAX	INTEGER
    ACCESS	read-only
		STATUS	current
		DESCRIPTION
			"The port number of the remote device."
		::=	{ raisecomAutoProvisionRemoteEntry	5 }

	raisecomAutoProvisionRemoteSysOID         OBJECT-TYPE
		SYNTAX	OCTET STRING (SIZE(1..64))
		ACCESS	read-only
		STATUS	current
		DESCRIPTION
			"The value of the system OID."
		::=	{ raisecomAutoProvisionRemoteEntry	6 }

	raisecomAutoProvisionRemoteStatus         OBJECT-TYPE
		SYNTAX	INTEGER
						{
              OK(0),
              FAIL(1)
            }
		ACCESS  read-only
		STATUS  current
		DESCRIPTION
			"The management status of remote device."
		::=	{ raisecomAutoProvisionRemoteEntry	7 }

	raisecomAutoProvisionRemoteVid            OBJECT-TYPE
		SYNTAX  INTEGER (1..4094)
		ACCESS  read-only
		STATUS  current
		DESCRIPTION
			"The VLAN ID of remote device."
		::=	{ raisecomAutoProvisionRemoteEntry	8 }

	-- END raisecomAutoProvisionRemoteTable

  raisecomAutoProvisionTrapGroup	  OBJECT IDENTIFIER ::= {	raisecomAutoProvisionMdev 3 }

  raisecomAutoProvisionRcvErrorAck            NOTIFICATION-TYPE
        OBJECTS{
            raisecomAutoProvisionRemoteMac,
            raisecomAutoProvisionRemoteStatus,
            raisecomAutoProvisionRemotePort,
            raisecomAutoProvisionRemoteVid
            }
        STATUS      current
        DESCRIPTION
        "Receiving ACK message with error code trap."
        ::= { raisecomAutoProvisionTrapGroup 1 }

  raisecomAutoProvisionSaveRemote        NOTIFICATION-TYPE
        OBJECTS{
            raisecomAutoProvisionRemoteMac,
            raisecomAutoProvisionRemoteStatus,
            raisecomAutoProvisionRemotePort,
            raisecomAutoProvisionRemoteVid
            }
        STATUS      current
        DESCRIPTION
        "Saving remote device information trap."
        ::= { raisecomAutoProvisionTrapGroup 2 }
END
