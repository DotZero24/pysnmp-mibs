--MibName=rcDot1x
-- =======================================================================
-- Version info
--
-- Version 1.0 Created 2005.07.27 by ZHANGJUN
-- This version of MIB is created just for the use of Network Management Systems
-- display and set the system configuration of 802.1x .
--
-- Copyright(c) 2002-2005 by RAISECOM TECH, Ltd.
-- =======================================================================


RAISECOM-DOT1X-MIB DEFINITIONS ::= BEGIN

	IMPORTS
 		MODULE-IDENTITY, OBJECT-TYPE,Unsigned32, TimeTicks
        FROM SNMPv2-SMI
        TruthValue
		FROM SNMPv2-TC
    	InterfaceIndex
        FROM IF-MIB
        iscomSwitch
    	FROM RAISECOM-BASE-MIB
    	dot1xPaePortEntry
    	FROM IEEE8021-PAE-MIB
	;
   	rcDot1x MODULE-IDENTITY

        LAST-UPDATED    "200711160000Z"
        ORGANIZATION    "Raisecom Science & Technology Co., ltd"
        CONTACT-INFO    "Raisecom Science & Technology Co., ltd.
                         E-mail: support@raisecom.com"

        DESCRIPTION     "Raisecom 802.1x MIB definition."
        ::= { iscomSwitch  27 }
		rcDot1xObjects OBJECT IDENTIFIER ::= { rcDot1x 1 }
------------------------------------------------------------------------------
--	define groups in RAISECOM-DOT1X-MIB
------------------------------------------------------------------------------
------------------------------------------------------------------------------
		rcDot1xConfig        OBJECT IDENTIFIER ::= { rcDot1xObjects 1 }
-- ---------------------------------------------------------- --

-- ---------------------------------------------------------- --
-- The PAE System Group
-- ---------------------------------------------------------- --


     	dot1xPortTable  OBJECT-TYPE
				SYNTAX		SEQUENCE OF	Dot1xPortEntry
				MAX-ACCESS	not-accessible
				STATUS		current
				DESCRIPTION
					 "A table of extend 802.1x port config."
				::=	{  rcDot1xConfig 1 }

			dot1xPortEntry  OBJECT-TYPE
				SYNTAX		Dot1xPortEntry
				MAX-ACCESS	not-accessible
				STATUS		current
				DESCRIPTION
				   	"A list of 802.1x port configuration parameters."
				AUGMENTS    { dot1xPaePortEntry }
				::=	{ dot1xPortTable 1 }

			Dot1xPortEntry ::=
		    SEQUENCE {
		        rcdot1xPortAuthControl
		            INTEGER,
				rcdot1xPortStatisticClear
					TruthValue,
	         	rcdot1xPortAuthMethod
	             	INTEGER
		        }

			rcdot1xPortAuthControl OBJECT-TYPE
		    SYNTAX      INTEGER { enabled(1), disabled(2) }
		    MAX-ACCESS  read-write
		    STATUS      current
		    DESCRIPTION
		        "The administrative enable/disable state for
				Port Access Control in a port."

		    ::= { dot1xPortEntry 1 }

			rcdot1xPortStatisticClear OBJECT-TYPE
		    SYNTAX      TruthValue
		    MAX-ACCESS  read-write
		    STATUS      current
		    DESCRIPTION
		        "clear “dot1xAuthStatsTable”  statistic  information"

		    ::= { dot1xPortEntry 2 }

	        rcdot1xPortAuthMethod OBJECT-TYPE
	        SYNTAX INTEGER {	portbased(1), macbased(2) }
	        MAX-ACCESS read-write
		    STATUS current
		    DESCRIPTION
		        "Auth method for port."
    	    DEFVAL { portbased }

	        ::= { dot1xPortEntry 3 }
END
