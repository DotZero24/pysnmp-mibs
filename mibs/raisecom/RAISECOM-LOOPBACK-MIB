-- *****************************************************************
-- RAISECOM-LOOPBACK-MIB.mib
--
-- August. 2012, guokai
--
-- Copyright(c) 2009-2010 by RAISECOM TECH, Ltd.
-- All rights reserved.
-- *****************************************************************


RAISECOM-LOOPBACK-MIB DEFINITIONS ::= BEGIN
IMPORTS
    Integer32,
    Counter32,
    Unsigned32,
    Gauge32
                    FROM SNMPv2-SMI
    MacAddress,
    RowStatus
                    FROM SNMPv2-TC     -- [RFC2579]
    IpAddress       FROM SNMPv2-SMI    -- [RFC2578]
    iscomSwitch
                    FROM RAISECOM-BASE-MIB;

rcLoopback  MODULE-IDENTITY
    LAST-UPDATED   "201208020000Z"
    ORGANIZATION   "Raisecom, Inc."
    CONTACT-INFO
                "       Raise Systems

                Postal: Beijing,
                        China

                   Tel: 86-010-82884499

                E-mail: guokai_yf@raisecom.com"
    DESCRIPTION
        "This MIB module defines objects to rcExtLoopback "
        REVISION   "201208020000Z"
        DESCRIPTION
            "The initial revision of this MIB."
        ::={ iscomSwitch  73}
--
--
-- rcLoopbackPortTable --
      --rcloopback
		--rcLoopbackPortTable
			--rcLoopbackPortEntry
				--rcLoopbackPortIndex
				--rcLoopbackPortEnable
				--rcLoopbackPortMode
				--rcLoopbackPortStatistics
				--rcLoopbackPortClearStatistics
				--rcLoopbackPortSmac



rcLoopbackPortTable  OBJECT-TYPE
    SYNTAX      SEQUENCE OF RcLoopbackPortEntry
    MAX-ACCESS  not-accessible
    STATUS      current
    DESCRIPTION
        "This table contains LoopBack control data."
    ::= { rcLoopback  1 }

--rcL2LoopbackPortTable  OBJECT IDENTIFIER ::= {rcLoopback 2}
--rcL3LoopbackPortTable  OBJECT IDENTIFIER ::= {rcLoopback 3}

rcLoopbackPortEntry   OBJECT-TYPE
    SYNTAX      RcLoopbackPortEntry
    MAX-ACCESS  not-accessible
    STATUS      current
    DESCRIPTION
        ""
	INDEX        { rcLoopbackPortIndex }
    ::={ rcLoopbackPortTable 1 }

RcLoopbackPortEntry ::= SEQUENCE {
        rcLoopbackPortIndex				         INTEGER,
        rcLoopbackPortEnable                     INTEGER,
        rcLoopbackPortMode                       INTEGER,
        rcLoopbackPortStatistics                 Counter32,
        rcLoopbackPortClearStatistics            INTEGER,
    	rcLoopbackPortSmac		             	 MacAddress,
    	rcLoopbackPortProtocol                   INTEGER,
    	rcLoopbackPortVlan                       INTEGER

	 	    }

rcLoopbackPortIndex       OBJECT-TYPE
	SYNTAX      INTEGER
	MAX-ACCESS  not-accessible
    STATUS      current
    DESCRIPTION
            "An index based on the equipment port number."
    ::= { rcLoopbackPortEntry 1 }

rcLoopbackPortEnable       OBJECT-TYPE
	SYNTAX      INTEGER   {
	                       disable(0),
	                       enable (1)
	                       }
	MAX-ACCESS  read-write
    STATUS      current
    DESCRIPTION
            "Specifies the status of Loopback.0:disable,1:l1 l2 l3 enable"
    DEFVAL          {disable}
   ::= { rcLoopbackPortEntry 2 }

rcLoopbackPortMode       OBJECT-TYPE
	SYNTAX      INTEGER     { l1(1), l2(2),l3(3)}
	MAX-ACCESS  read-write
    STATUS      current
    DESCRIPTION
            "Specifies the status of Loopback.1:l1,2:l2,3:l3"
   DEFVAL          {l1}
   ::= { rcLoopbackPortEntry 3 }

rcLoopbackPortStatistics  OBJECT-TYPE
	SYNTAX      Counter32
	MAX-ACCESS  read-only
    STATUS      current
    DESCRIPTION
          "The statistics of loopback packet."
    ::= { rcLoopbackPortEntry 4 }

rcLoopbackPortClearStatistics  OBJECT-TYPE
	SYNTAX      INTEGER    { disable(0), enable(1)}
    MAX-ACCESS  read-write
    STATUS      current
    DESCRIPTION
            "Clear the statistics of loopback packet.0:disable,1:enable"
     DEFVAL          {disable}
    ::= { rcLoopbackPortEntry 5 }

rcLoopbackPortSmac      OBJECT-TYPE
	SYNTAX      MacAddress
    MAX-ACCESS  read-write
    STATUS      current
    DESCRIPTION
            "Specifies the destination MAC address of L2 Loopback."

    ::= { rcLoopbackPortEntry 6 }

rcLoopbackPortProtocol   OBJECT-TYPE
	SYNTAX      INTEGER
    MAX-ACCESS  read-write
    STATUS      current
    DESCRIPTION
            "Specifies the protocol of L2 Loopback."
    ::= { rcLoopbackPortEntry 7 }

rcLoopbackPortVlan   OBJECT-TYPE
	SYNTAX      INTEGER
    MAX-ACCESS  read-write
    STATUS      current
    DESCRIPTION
            "vlan of L2 Loopback."
    DEFVAL   {1}
    ::= { rcLoopbackPortEntry 8 }


rcL2LoopbackPortTable  OBJECT-TYPE
    SYNTAX      SEQUENCE OF RcL2LoopbackPortEntry
    MAX-ACCESS  not-accessible
    STATUS      current
    DESCRIPTION
        "This table contains L2 Loopback control data."
    ::= { rcLoopback  2 }

rcL2LoopbackPortEntry   OBJECT-TYPE
    SYNTAX      RcL2LoopbackPortEntry
    MAX-ACCESS  not-accessible
    STATUS      current
    DESCRIPTION
        ""
	INDEX        { rcLoopbackPortIndex, rcL2LoopbackPortNum}
    ::={ rcL2LoopbackPortTable 1 }

RcL2LoopbackPortEntry ::= SEQUENCE {
        rcL2LoopbackPortNum				         INTEGER,
        rcL2LoopbackPortStatistics                 Counter32,
    	rcL2LoopbackPortSmac		             	 MacAddress,
    	rcL2LoopbackPortProtocol                   INTEGER,
    	rcL2LoopbackPortVlan                       INTEGER,
    	rcL2LoopbackPortStatus                     RowStatus

	 	    }

rcL2LoopbackPortNum       OBJECT-TYPE
	SYNTAX      INTEGER
	MAX-ACCESS  not-accessible
    STATUS      current
    DESCRIPTION
            "An index based on the loopback rule number."
    ::= { rcL2LoopbackPortEntry 1 }

rcL2LoopbackPortStatistics  OBJECT-TYPE
	SYNTAX      Counter32
	MAX-ACCESS  read-only
    STATUS      current
    DESCRIPTION
          "The statistics of loopback packet."
    ::= { rcL2LoopbackPortEntry 2 }

rcL2LoopbackPortSmac      OBJECT-TYPE
	SYNTAX      MacAddress
    MAX-ACCESS  read-create
    STATUS      current
    DESCRIPTION
            "Specifies the destination MAC address of L2 Loopback."

    ::= { rcL2LoopbackPortEntry 3 }

rcL2LoopbackPortProtocol   OBJECT-TYPE
	SYNTAX      INTEGER
    MAX-ACCESS  read-create
    STATUS      current
    DESCRIPTION
            "Specifies the protocol of L2 Loopback."
    ::= { rcL2LoopbackPortEntry 4 }

rcL2LoopbackPortVlan   OBJECT-TYPE
	SYNTAX      INTEGER
    MAX-ACCESS  read-create
    STATUS      current
    DESCRIPTION
            "vlan of L2 Loopback."
    DEFVAL   {1}
    ::= { rcL2LoopbackPortEntry 5 }

rcL2LoopbackPortStatus   OBJECT-TYPE
	SYNTAX      RowStatus
    MAX-ACCESS  read-create
    STATUS      current
    DESCRIPTION
            "Row status of loopback rule."
    ::= { rcL2LoopbackPortEntry 6 }


rcL3LoopbackPortTable  OBJECT-TYPE
    SYNTAX      SEQUENCE OF RcL3LoopbackPortEntry
    MAX-ACCESS  not-accessible
    STATUS      current
    DESCRIPTION
        "This table contains L3 Loopback control data."
    ::= { rcLoopback  3 }

rcL3LoopbackPortEntry   OBJECT-TYPE
    SYNTAX      RcL3LoopbackPortEntry
    MAX-ACCESS  not-accessible
    STATUS      current
    DESCRIPTION
        ""
	INDEX        { rcLoopbackPortIndex, rcL3LoopbackPortNum}
    ::={ rcL3LoopbackPortTable 1 }

RcL3LoopbackPortEntry ::= SEQUENCE {
        rcL3LoopbackPortNum				         INTEGER,
        rcL3LoopbackPortDestAddr           IpAddress,
        rcL3LoopbackPortMAC                        MacAddress,
        rcL3LoopbackPortSvlan                       INTEGER,
        rcL3LoopbackPortCvlan                       INTEGER,
        rcL3LoopbackPortDscp                       Integer32 (0..63 ),
     	rcL3LoopbackPortStatus                     RowStatus

	 	    }

rcL3LoopbackPortNum       OBJECT-TYPE
	SYNTAX      INTEGER
	MAX-ACCESS  not-accessible
    STATUS      current
    DESCRIPTION
            "An index based on the L3 loopback rule number."
    ::= { rcL3LoopbackPortEntry 1 }

rcL3LoopbackPortDestAddr      OBJECT-TYPE
	SYNTAX      IpAddress
    MAX-ACCESS  read-create
    STATUS      current
    DESCRIPTION
            "Specifies the Destination ip address of L3 Loopback."

    ::= { rcL3LoopbackPortEntry 2 }

rcL3LoopbackPortMAC      OBJECT-TYPE
	SYNTAX      MacAddress
    MAX-ACCESS  read-create
    STATUS      current
    DESCRIPTION
            "Specifies the next hop MAC address of L3 Loopback."

    ::= { rcL3LoopbackPortEntry 3 }

 rcL3LoopbackPortSvlan   OBJECT-TYPE
	SYNTAX      INTEGER
    MAX-ACCESS  read-create
    STATUS      current
    DESCRIPTION
            "Svlan of L3 Loopback."
    DEFVAL   {1}
    ::= { rcL3LoopbackPortEntry 4 }

rcL3LoopbackPortCvlan   OBJECT-TYPE
	SYNTAX      INTEGER
    MAX-ACCESS  read-create
    STATUS      current
    DESCRIPTION
            "Cvlan of L3 Loopback."
    DEFVAL   {1}
    ::= { rcL3LoopbackPortEntry 5 }

rcL3LoopbackPortDscp   OBJECT-TYPE
	SYNTAX      Integer32 (0..63 )
    MAX-ACCESS  read-create
    STATUS      current
    DESCRIPTION
            "Dscp of L3 Loopback."
    DEFVAL   {0}
    ::= { rcL3LoopbackPortEntry 6 }

rcL3LoopbackPortStatus   OBJECT-TYPE
	SYNTAX      RowStatus
    MAX-ACCESS  read-create
    STATUS      current
    DESCRIPTION
            "Row status of L3 loopback rule."
    ::= { rcL3LoopbackPortEntry 7 }

END
