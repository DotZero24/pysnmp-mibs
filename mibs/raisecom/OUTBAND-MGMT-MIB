-- -------------------------------------------------------------------------- --
-- -------------------------------------------------------------------------- --
--
--  File         : raisecom-outband-mgmt-mib.mi2
--  Description  : Raisecom EPON software mib defination
--  Version      : 1.0
--  Date         : Aug 24, 2006
--  Author		 : ghw
--  Copyright (c) 2006-2007 Beijing Raisecom Science & Technology Co., ltd
--  All Rights Reserved.
--
-- -------------------------------------------------------------------------- --
-- -------------------------------------------------------------------------- --

    OUTBAND-MGMT-MIB DEFINITIONS ::= BEGIN

    IMPORTS
        MODULE-IDENTITY, OBJECT-TYPE,
        Integer32,
        IpAddress               FROM SNMPv2-SMI
        RowStatus               FROM SNMPv2-TC
        iscomEpon               FROM RAISECOM-BASE-MIB;

    rcOutbandMgmt MODULE-IDENTITY

        LAST-UPDATED    "200702090000Z"  -- Aug 24, 2006
        ORGANIZATION    "Raisecom Science & Technology Co., ltd"
        CONTACT-INFO    "Raisecom Science & Technology Co., ltd.
                         E-mail: support@raisecom.com"

        DESCRIPTION     "iscom EPON OUT-BAND MIB definition."

        REVISION        "200702090000Z"  -- Aug 24, 2006
        DESCRIPTION     "Initial MIB creation."

                ::= { iscomEpon 3 }

-- -------------------------------------------------------------------------- --
    rcOutbandIpSubnet           OBJECT IDENTIFIER ::= { rcOutbandMgmt 1 }
-- -------------------------------------------------------------------------- --
    rcOutbandIpSubnetTable OBJECT-TYPE
        SYNTAX SEQUENCE OF RcOutbandIpSubnetEntry
        MAX-ACCESS not-accessible
        STATUS current
        DESCRIPTION
            "A table of subnet parameters.  There is one entry
             available for each of the 'rcL3IpSubnetMaxRows'
             supported IP subnets."
        ::= { rcOutbandIpSubnet 1 }

    rcOutbandIpSubnetEntry OBJECT-TYPE
        SYNTAX RcOutbandIpSubnetEntry
        MAX-ACCESS not-accessible
        STATUS current
        DESCRIPTION
            "A list of subnet parameters."
        INDEX { rcOutbandIpSubnetIndex }
        ::= { rcOutbandIpSubnetTable 1 }

    RcOutbandIpSubnetEntry ::= SEQUENCE {
        rcOutbandIpSubnetIndex     	Integer32,
        rcOutbandIpSubnetIpAddress  IpAddress,
        rcOutbandIpSubnetMask       IpAddress,
        rcOutbandIpSubnetRowStatus  RowStatus
        }

    rcOutbandIpSubnetIndex  OBJECT-TYPE
        SYNTAX Integer32
        MAX-ACCESS not-accessible
        STATUS current
        DESCRIPTION
            "DURABLE:
             The index associated with this subnet."
        ::= { rcOutbandIpSubnetEntry 1 }

    rcOutbandIpSubnetIpAddress  OBJECT-TYPE
        SYNTAX IpAddress
        MAX-ACCESS read-create
        STATUS current
        DESCRIPTION
            "DURABLE:
             The network management station uses this IP Address to talk
             with the Agent on this subnet.  This IP address logically
             AND'ed with 'rcOutbandIpSubnetMask' yields the actual subnet
             value for this subnet."
        ::= { rcOutbandIpSubnetEntry 2 }

    rcOutbandIpSubnetMask  OBJECT-TYPE
        SYNTAX IpAddress
        MAX-ACCESS read-create
        STATUS current
        DESCRIPTION
            "DURABLE:
             The subnet mask for this subnet.  It contains 1's in the
             bit positions for the net and subnet IDs and 0's in the
             bit positions for host ID.  The 1's must be contiguous,
             starting with the left most bit."
        ::= { rcOutbandIpSubnetEntry 3 }

    rcOutbandIpSubnetRowStatus OBJECT-TYPE
        SYNTAX  RowStatus
        MAX-ACCESS  read-create
        STATUS  current
        DESCRIPTION
            "DURABLE:
             This object indicates the status of this entry.  A row in this
             table must be created using the createAndWait(5) action state
             (i.e., createAndGo(4) is not supported).  This object can only
             be set to active(1) after all objects for this row are valid.
             The 'rcL3IpSubnetName' is optional.

             Note that the notInService(2) state is not supported.  Objects
             in this table row can be changed when this object is notReady(3)
             or active(1)."
        ::= { rcOutbandIpSubnetEntry 4 }
--
-- END of OUTBAND-MGMT-MIB
--

END
