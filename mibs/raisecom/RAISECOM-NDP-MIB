-- *****************************************************************
-- RAISECOM-NDP-MIB.mib
--
--  December 2011, wuxia
--
-- Copyright(c) 2011-2013 by RAISECOM TECH, Ltd.
-- All rights reserved.
-- *****************************************************************

--MibName=raisecomNdp
RAISECOM-NDP-MIB DEFINITIONS ::= BEGIN

IMPORTS
    MODULE-IDENTITY, OBJECT-TYPE, Counter32, Gauge32,
    Integer32, Unsigned32, IpAddress, mib-2
                 FROM SNMPv2-SMI
    TEXTUAL-CONVENTION, TruthValue, RowStatus, TimeStamp
                 FROM SNMPv2-TC
    EnableVar	 FROM SWITCH-TC
    InterfaceIndex
                 FROM IF-MIB
    raisecomAgent
                 FROM RAISECOM-BASE-MIB;

    raisecomNdp MODULE-IDENTITY
        LAST-UPDATED    "201112120000Z"  -- Dec 12, 2011
        ORGANIZATION    "Raisecom, Inc."
        CONTACT-INFO
                "       Raise Systems
                        Postal: Beijing, China
                        Tel: 86-010-82884499
                        E-mail: support@raisecom.com"

        DESCRIPTION     "This MIB module defines objects to Ndp."

        REVISION        "201112120000Z"  -- Dec 12, 2011
        DESCRIPTION     "Initial MIB creation."

        ::= { raisecomAgent 66}

------------------------------------------------------------------------------
--  Define groups in RAISECOM-NDP-MIB
------------------------------------------------------------------------------

    raisecomNdpObjects              OBJECT IDENTIFIER ::= { raisecomNdp 1 }

------------------------------------------------------------------------------
--
--   raisecomNdpObjects
--
--   This group defines all the objects related to Ndp.
------------------------------------------------------------------------------

------------------------------------------------------------------------------
--  Define groups in raisecomNdpObjects
------------------------------------------------------------------------------
    raisecomNdpIfTable              OBJECT IDENTIFIER ::= { raisecomNdpObjects 1 }
------------------------------------------------------------------------------

--raisecomNdpIfTable
raisecomNdpIfTable OBJECT-TYPE
    SYNTAX SEQUENCE OF RaisecomNdpIfEntry
    MAX-ACCESS not-accessible
    STATUS current
    DESCRIPTION
        "The NDP Interface Table ."
    ::=  { raisecomNdpObjects 1 }

raisecomNdpIfEntry OBJECT-TYPE
    SYNTAX RaisecomNdpIfEntry
    MAX-ACCESS not-accessible
    STATUS current
    DESCRIPTION
        "The NDP Interface Table entry."
    INDEX {raisecomNdpIfIndex}
    ::=  {raisecomNdpIfTable 1 }

RaisecomNdpIfEntry ::= SEQUENCE {
    raisecomNdpIfIndex     InterfaceIndex,
    raisecomNdpDadNsNum    Unsigned32,
    raisecomNdpMaxLearnNum    Unsigned32
    }

raisecomNdpIfIndex OBJECT-TYPE
    SYNTAX InterfaceIndex
    MAX-ACCESS not-accessible
    STATUS current
    DESCRIPTION
        "The index value that uniquely identifies the interface to which this entry is applicable."
    ::=  { raisecomNdpIfEntry 1 }

raisecomNdpDadNsNum  OBJECT-TYPE
    SYNTAX Unsigned32(0..600)
    MAX-ACCESS read-create
    STATUS current
    DESCRIPTION
        "The number of NS for duplicate address detection."
    DEFVAL { 1 }
    ::= { raisecomNdpIfEntry  2 }

raisecomNdpMaxLearnNum  OBJECT-TYPE
    SYNTAX Unsigned32
    MAX-ACCESS read-create
    STATUS current
    DESCRIPTION
        "The max number of ndp."
    ::= { raisecomNdpIfEntry  3 }



END
