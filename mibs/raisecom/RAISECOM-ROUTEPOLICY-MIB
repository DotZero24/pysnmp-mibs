--MibName=routepolicy
-- *****************************************************************
-- RAISECOM-ROUTEPOLICY-MIB.MIB:  Raisecom RoutePolicy MIB file
-- Feb 2012, Yg
--
-- Copyright (c) 2012 by Raisecom, Inc.
-- All rights reserved.
--
-- *****************************************************************
RAISECOM-ROUTEPOLICY-MIB DEFINITIONS ::= BEGIN

    IMPORTS
        MODULE-IDENTITY, OBJECT-TYPE,
        Counter32, IpAddress                    FROM SNMPv2-SMI
        RowStatus                               FROM SNMPv2-TC
        raisecomAgent	            	        FROM RAISECOM-BASE-MIB;

    raisecomRoutePolicy MODULE-IDENTITY
        LAST-UPDATED    "0412200000Z"  -- Dec 20, 2004
        ORGANIZATION    "Wind River Systems, Inc."
        CONTACT-INFO    "Wind River Systems, Inc.
                         E-mail: support@windriver.com"

        DESCRIPTION     "description of raisecomRoutePolicyMIB object."

        REVISION        "0412200000Z"  -- Dec 20, 2004
        DESCRIPTION     "Initial MIB creation."

        ::= {raisecomAgent 76}


--------------------------------------------------------------------------------------
--  groups in the ROSE Layer 3 MIB
--------------------------------------------------------------------------------------
    raisecomRoutePolicyNotifications            OBJECT IDENTIFIER ::={ raisecomRoutePolicy 1 }
    raisecomRoutePolicyObjects                  OBJECT IDENTIFIER ::={ raisecomRoutePolicy 2 }
    raisecomRoutePolicyConformance              OBJECT IDENTIFIER ::={ raisecomRoutePolicy 3 }
---------------------------------------------------------------------------------------

--------------------------------------------------------------------------------------
--  groups in the ROSE Layer 3 MIB
--------------------------------------------------------------------------------------
    raisecomRoutePolicyScalar                 OBJECT IDENTIFIER ::={ raisecomRoutePolicyObjects 1 }
    raisecomRoutePolicyIpPrefixList           OBJECT IDENTIFIER ::={ raisecomRoutePolicyObjects 2 }
    raisecomRoutePolicyRouteMap               OBJECT IDENTIFIER ::={ raisecomRoutePolicyObjects 3 }
---------------------------------------------------------------------------------------


--------------------------------------------------------------------------------------
--  groups in the ROSE Layer 3 MIB
--------------------------------------------------------------------------------------
    raisecomRoutePolicyIpPrefixListScalar     OBJECT IDENTIFIER ::={ raisecomRoutePolicyIpPrefixList 1 }
---------------------------------------------------------------------------------------

--------------------------------------------------------------------------------------
--  groups in the ROSE Layer 3 MIB
--------------------------------------------------------------------------------------
    raisecomRoutePolicyRouteMapScalar         OBJECT IDENTIFIER ::={ raisecomRoutePolicyRouteMap 1 }
---------------------------------------------------------------------------------------

-- -------------------------------------------------------------
-- scalar in the MIB
-- -------------------------------------------------------------
--raisecomRoutePolicyIpPrefixListScalar
    raisecomRoutePolicyIpPrefixListTableNextIndex  OBJECT-TYPE
        SYNTAX INTEGER (0..400)
        MAX-ACCESS read-only
        STATUS current
        DESCRIPTION
            "The value from 1 to 400 means the next available
			index of ip-preifx-list table, 0 means no available
			index."
        DEFVAL          { 0 }
        ::= { raisecomRoutePolicyIpPrefixListScalar 1 }

--raisecomRoutePolicyRouteMapScalar
    raisecomRoutePolicyRouteMapTableNextIndex  OBJECT-TYPE
        SYNTAX INTEGER (0..400)
        MAX-ACCESS read-only
        STATUS current
        DESCRIPTION
            "The value from 1 to 400 means the next available
			index of route-map table，0 means no available index."
        DEFVAL          { 0 }
        ::= { raisecomRoutePolicyRouteMapScalar 1 }

------------------------------------------------------------------
--prefix table in the mib
------------------------------------------------------------------

--raisecomRoutePolicyIpPrefixListTable

    raisecomRoutePolicyIpPrefixListTable      OBJECT-TYPE
        SYNTAX   SEQUENCE OF RaisecomRoutePolicyIpPrefixListEntry
        MAX-ACCESS	 not-accessible
        STATUS   current
        DESCRIPTION
                 "IP-Prefix-List Table"
        ::= { raisecomRoutePolicyIpPrefixList   2 }

    raisecomRoutePolicyIpPrefixListEntry   OBJECT-TYPE
        SYNTAX RaisecomRoutePolicyIpPrefixListEntry
        MAX-ACCESS not-accessible
        STATUS current
        DESCRIPTION
            "An entry in raisecomRoutePolicyIpPrefixListTable."
        INDEX { raisecomRoutePolicyIpPrefixListIndex}
        ::= { raisecomRoutePolicyIpPrefixListTable 1 }

    RaisecomRoutePolicyIpPrefixListEntry  ::= SEQUENCE {
        raisecomRoutePolicyIpPrefixListIndex          INTEGER ,
        raisecomRoutePolicyIpPrefixListName           OCTET STRING,
        raisecomRoutePolicyIpPrefixListNextNodeSeq    INTEGER,
        raisecomRoutePolicyIpPrefixListRowStatus      RowStatus
    }

    raisecomRoutePolicyIpPrefixListIndex  OBJECT-TYPE
        SYNTAX INTEGER
        MAX-ACCESS not-accessible
        STATUS current
        DESCRIPTION
            "The value of this object indicates the index of
			ip-prefix-list table."
        ::= { raisecomRoutePolicyIpPrefixListEntry 1 }

    raisecomRoutePolicyIpPrefixListName  OBJECT-TYPE
        SYNTAX OCTET STRING (SIZE(1..19))
        MAX-ACCESS read-create
        STATUS current
        DESCRIPTION
            "The value of this object indicates the name of an
			ip-prefix-list."
        ::= { raisecomRoutePolicyIpPrefixListEntry 2 }

     raisecomRoutePolicyIpPrefixListNextNodeSeq OBJECT-TYPE
        SYNTAX INTEGER
        MAX-ACCESS read-only
        STATUS current
        DESCRIPTION
            "The value of this object indicates the next auto
            build sequence of an ip-prefix-list node."
        ::= { raisecomRoutePolicyIpPrefixListEntry 3 }

    raisecomRoutePolicyIpPrefixListRowStatus  OBJECT-TYPE
        SYNTAX RowStatus
        MAX-ACCESS read-create
        STATUS current
        DESCRIPTION
            "This object allows entries to be created and deleted
			in the raisecomRoutePolicyIpPrefixListTable."
        ::= { raisecomRoutePolicyIpPrefixListEntry 4 }

--raisecomRoutePolicyIpPrefixListNodeTable

    raisecomRoutePolicyIpPrefixListNodeTable      OBJECT-TYPE
        SYNTAX   SEQUENCE OF RaisecomRoutePolicyIpPrefixListNodeEntry
        MAX-ACCESS	 not-accessible
        STATUS   current
        DESCRIPTION
                 "IP-Prefix-List NodeTable"
        ::= { raisecomRoutePolicyIpPrefixList   3 }

    raisecomRoutePolicyIpPrefixListNodeEntry   OBJECT-TYPE
        SYNTAX RaisecomRoutePolicyIpPrefixListNodeEntry
        MAX-ACCESS not-accessible
        STATUS current
        DESCRIPTION
            "An entry in raisecomRoutePolicyIpPrefixListNodeTable."
        INDEX {
        	   raisecomRoutePolicyIpPrefixListIndex,
               raisecomRoutePolicyIpPrefixListNodeSeq}
        ::= { raisecomRoutePolicyIpPrefixListNodeTable 1 }

    RaisecomRoutePolicyIpPrefixListNodeEntry  ::= SEQUENCE {
        raisecomRoutePolicyIpPrefixListNodeSeq           INTEGER,
        raisecomRoutePolicyIpPrefixListNodeMode          INTEGER,
        raisecomRoutePolicyIpPrefixListNodePrefix        IpAddress,
		raisecomRoutePolicyIpPrefixListNodePrefixLen     INTEGER,
		raisecomRoutePolicyIpPrefixListNodePrefixLenMin  INTEGER,
		raisecomRoutePolicyIpPrefixListNodePrefixLenMax  INTEGER,
		raisecomRoutePolicyIpPrefixListNodeRowStatus     RowStatus
        }

    raisecomRoutePolicyIpPrefixListNodeSeq  OBJECT-TYPE
        SYNTAX INTEGER (1..65535)
        MAX-ACCESS not-accessible
        STATUS current
        DESCRIPTION
            "The value of this object indicates the index of ip-prefix-list-node table."
        ::= { raisecomRoutePolicyIpPrefixListNodeEntry 1 }

    raisecomRoutePolicyIpPrefixListNodeMode  OBJECT-TYPE
        SYNTAX INTEGER {
						permit (0) ,
						deny   (1)
					   }
        MAX-ACCESS read-create
        STATUS current
        DESCRIPTION
            "permit means specifing a permit rule , deny means specifing a deny rule"
        ::= { raisecomRoutePolicyIpPrefixListNodeEntry 2 }

    raisecomRoutePolicyIpPrefixListNodePrefix  OBJECT-TYPE
        SYNTAX IpAddress
        MAX-ACCESS read-create
        STATUS current
        DESCRIPTION
            "IP address of an ip-prefix-list node."
        ::= { raisecomRoutePolicyIpPrefixListNodeEntry 3 }

	raisecomRoutePolicyIpPrefixListNodePrefixLen  OBJECT-TYPE
        SYNTAX INTEGER (0..32)
        MAX-ACCESS read-create
        STATUS current
        DESCRIPTION
            "Mask length of an ip-prefix-list-node."
        ::= { raisecomRoutePolicyIpPrefixListNodeEntry 4 }

    raisecomRoutePolicyIpPrefixListNodePrefixLenMin  OBJECT-TYPE
        SYNTAX INTEGER (0..32)
        MAX-ACCESS read-create
        STATUS current
        DESCRIPTION
            "The greater-than-or-equal-to value of the mask length,
            0 represents for no setting of GE value."
        ::= { raisecomRoutePolicyIpPrefixListNodeEntry 5 }

	raisecomRoutePolicyIpPrefixListNodePrefixLenMax  OBJECT-TYPE
        SYNTAX INTEGER (0..32)
        MAX-ACCESS read-create
        STATUS current
        DESCRIPTION
            "The less-than-or-equal-to value of the mask length,
            0 represents for no setting of LE value."
        ::= { raisecomRoutePolicyIpPrefixListNodeEntry 6 }

	raisecomRoutePolicyIpPrefixListNodeRowStatus  OBJECT-TYPE
        SYNTAX RowStatus
        MAX-ACCESS read-create
        STATUS current
        DESCRIPTION
            "This object allows entries to be created and deleted 	in the raisecomRoutePolicyIpPrefixListNodeTable."
        ::= { raisecomRoutePolicyIpPrefixListNodeEntry 7 }

--raisecomRoutePolicyIpPrefixListStatisticsTable

    raisecomRoutePolicyIpPrefixListStatisticsTable      OBJECT-TYPE
        SYNTAX   SEQUENCE OF RaisecomRoutePolicyIpPrefixListStatisticsEntry
        MAX-ACCESS	 not-accessible
        STATUS   current
        DESCRIPTION
                 "IP-Prefix-List Statistics Table"
        ::= { raisecomRoutePolicyIpPrefixList   4 }

    raisecomRoutePolicyIpPrefixListStatisticsEntry   OBJECT-TYPE
        SYNTAX RaisecomRoutePolicyIpPrefixListStatisticsEntry
        MAX-ACCESS not-accessible
        STATUS current
        DESCRIPTION
            "An entry in raisecomRoutePolicyIpPrefixListStatisticsTable."
        INDEX { raisecomRoutePolicyIpPrefixListIndex}
        ::= { raisecomRoutePolicyIpPrefixListStatisticsTable 1 }

    RaisecomRoutePolicyIpPrefixListStatisticsEntry  ::= SEQUENCE {
        raisecomRoutePolicyIpPrefixListStatsNodes          Counter32,
        raisecomRoutePolicyIpPrefixListRefCount            Counter32,
		raisecomRoutePolicyIpPrefixListStatsPermits        Counter32,
		raisecomRoutePolicyIpPrefixListStatsDenies         Counter32
        }

    raisecomRoutePolicyIpPrefixListStatsNodes  OBJECT-TYPE
        SYNTAX Counter32
        MAX-ACCESS read-only
        STATUS current
        DESCRIPTION
            "The number of ip-prefix-list-node."
        ::= { raisecomRoutePolicyIpPrefixListStatisticsEntry 1 }

    raisecomRoutePolicyIpPrefixListRefCount  OBJECT-TYPE
        SYNTAX Counter32
        MAX-ACCESS read-only
        STATUS current
        DESCRIPTION
            "The reference count of an ip-prefix-list."
        ::= { raisecomRoutePolicyIpPrefixListStatisticsEntry 2 }

    raisecomRoutePolicyIpPrefixListStatsPermits  OBJECT-TYPE
        SYNTAX Counter32
        MAX-ACCESS read-only
        STATUS current
        DESCRIPTION
            "The count that the ip-prefix-list has permitted."
        ::= { raisecomRoutePolicyIpPrefixListStatisticsEntry 3 }

	raisecomRoutePolicyIpPrefixListStatsDenies  OBJECT-TYPE
        SYNTAX Counter32
        MAX-ACCESS read-only
        STATUS current
        DESCRIPTION
            "The count that the ip-prefix-list has has denied."
        ::= { raisecomRoutePolicyIpPrefixListStatisticsEntry 4 }

------------------------------------------------------------------
--routemap table in the mib
------------------------------------------------------------------

--raisecomRoutePolicyRouteMapTable

    raisecomRoutePolicyRouteMapTable    OBJECT-TYPE
        SYNTAX   SEQUENCE OF RaisecomRoutePolicyRouteMapEntry
        MAX-ACCESS	 not-accessible
        STATUS   current
        DESCRIPTION
                 "Route-Map Table"
        ::= { raisecomRoutePolicyRouteMap   2 }

    raisecomRoutePolicyRouteMapEntry   OBJECT-TYPE
        SYNTAX RaisecomRoutePolicyRouteMapEntry
        MAX-ACCESS not-accessible
        STATUS current
        DESCRIPTION
            "An entry in raisecomRoutePolicyRouteMapTable."
        INDEX { raisecomRoutePolicyRouteMapIndex}
        ::= { raisecomRoutePolicyRouteMapTable 1 }

    RaisecomRoutePolicyRouteMapEntry  ::= SEQUENCE {
        raisecomRoutePolicyRouteMapIndex          INTEGER,
        raisecomRoutePolicyRouteMapName           OCTET STRING,
        raisecomRoutePolicyRouteMapRowStatus      RowStatus
    }

    raisecomRoutePolicyRouteMapIndex  OBJECT-TYPE
        SYNTAX INTEGER
        MAX-ACCESS not-accessible
        STATUS current
        DESCRIPTION
            "The value of this object indicates the index of route-map table."
        ::= { raisecomRoutePolicyRouteMapEntry 1 }

    raisecomRoutePolicyRouteMapName  OBJECT-TYPE
        SYNTAX OCTET STRING (SIZE(1..19))
        MAX-ACCESS read-create
        STATUS current
        DESCRIPTION
            "The value of this node indicates the name of route-map."
        ::= { raisecomRoutePolicyRouteMapEntry 2 }

    raisecomRoutePolicyRouteMapRowStatus  OBJECT-TYPE
        SYNTAX RowStatus
        MAX-ACCESS read-create
        STATUS current
        DESCRIPTION
            "This object allows entries to be created and deleted in the raisecomRoutePolicyRouteMapTable."
        ::= { raisecomRoutePolicyRouteMapEntry 3 }

--raisecomRoutePolicyRouteMapNodeTable

    raisecomRoutePolicyRouteMapNodeTable      OBJECT-TYPE
        SYNTAX   SEQUENCE OF RaisecomRoutePolicyRouteMapNodeEntry
        MAX-ACCESS	 not-accessible
        STATUS   current
        DESCRIPTION
                 "Route-Map-NodeTable"
        ::= { raisecomRoutePolicyRouteMap   3 }

    raisecomRoutePolicyRouteMapNodeEntry   OBJECT-TYPE
        SYNTAX RaisecomRoutePolicyRouteMapNodeEntry
        MAX-ACCESS not-accessible
        STATUS current
        DESCRIPTION
            "An entry in raisecomRoutePolicyRouteMapNodeTable."
        INDEX { raisecomRoutePolicyRouteMapIndex,
        		raisecomRoutePolicyRouteMapNodeSeq}
        ::= { raisecomRoutePolicyRouteMapNodeTable 1 }

    RaisecomRoutePolicyRouteMapNodeEntry  ::= SEQUENCE {
        raisecomRoutePolicyRouteMapNodeSeq                    INTEGER,
        raisecomRoutePolicyRouteMapNodeMode                   INTEGER,
        raisecomRoutePolicyRouteMapNodeMatchFlag              BITS,
		raisecomRoutePolicyRouteMapNodeSetFlag                BITS,
		raisecomRoutePolicyRouteMapNodeMatchIpAclNum          INTEGER,
		raisecomRoutePolicyRouteMapNodeMatchIpPrefixListName  OCTET STRING,
		raisecomRoutePolicyRouteMapNodeMatchRouteType         BITS ,
		raisecomRoutePolicyRouteMapNodeMatchTag               INTEGER,
		raisecomRoutePolicyRouteMapNodeMatchMetric            INTEGER,
		raisecomRoutePolicyRouteMapNodeSetLevel               INTEGER,
		raisecomRoutePolicyRouteMapNodeSetTag                 INTEGER,
		raisecomRoutePolicyRouteMapNodeSetMetricRule          INTEGER,
		raisecomRoutePolicyRouteMapNodeSetMetric              INTEGER,
		raisecomRoutePolicyRouteMapNodeSetMetricType          INTEGER,
		raisecomRoutePolicyRouteMapNodeRowStatus              RowStatus
        }

    raisecomRoutePolicyRouteMapNodeSeq  OBJECT-TYPE
        SYNTAX INTEGER (1..65535)
        MAX-ACCESS not-accessible
        STATUS current
        DESCRIPTION
            "The value of this node indicates the index of route-map-node table."
        ::= { raisecomRoutePolicyRouteMapNodeEntry 1 }

    raisecomRoutePolicyRouteMapNodeMode  OBJECT-TYPE
        SYNTAX INTEGER {
						permit (0),
						deny   (1)
					   }
        MAX-ACCESS read-create
        STATUS current
        DESCRIPTION
            "permit means specifing a permit rule , deny means specifing a deny rule."
        ::= { raisecomRoutePolicyRouteMapNodeEntry 2 }

    raisecomRoutePolicyRouteMapNodeMatchFlag  OBJECT-TYPE
        SYNTAX BITS {
					ip-prefix-list   (0),
					ip-acl-num       (1),
					metric           (2),
					tag              (3),
					route-type       (4)
					}
        MAX-ACCESS read-create
        STATUS current
        DESCRIPTION
            "This object indicates which node to be matched."
        ::= { raisecomRoutePolicyRouteMapNodeEntry 3 }

	raisecomRoutePolicyRouteMapNodeSetFlag  OBJECT-TYPE
        SYNTAX BITS {
					metric-rule   (0),
					metric        (1),
					metric-type   (2),
					tag           (3),
					level         (4)
					}
        MAX-ACCESS read-create
        STATUS current
        DESCRIPTION
            "This object indicates which node to be set."
        ::= { raisecomRoutePolicyRouteMapNodeEntry 4 }

    raisecomRoutePolicyRouteMapNodeMatchIpAclNum  OBJECT-TYPE
        SYNTAX INTEGER
        MAX-ACCESS read-create
        STATUS current
        DESCRIPTION
            "Specify match criteria that is an IP ACL for route-map-node."
        ::= { raisecomRoutePolicyRouteMapNodeEntry 5 }

	raisecomRoutePolicyRouteMapNodeMatchIpPrefixListName  OBJECT-TYPE
        SYNTAX OCTET STRING (SIZE(1..19))
        MAX-ACCESS read-create
        STATUS current
        DESCRIPTION
            "Specify match criteria that is an ip-prefix-list name for route-map."
        ::= { raisecomRoutePolicyRouteMapNodeEntry 6 }

	raisecomRoutePolicyRouteMapNodeMatchRouteType  OBJECT-TYPE
        SYNTAX BITS {
					internel             (0),
					external-type1       (1),
					external-type2       (2),
					nssa-external-type1  (3),
					nssa-external-type2  (4)
					}
        MAX-ACCESS read-create
        STATUS current
        DESCRIPTION
            "Specify match criteria that is route-type for route-map."
        ::= { raisecomRoutePolicyRouteMapNodeEntry 7 }

	raisecomRoutePolicyRouteMapNodeMatchTag  OBJECT-TYPE
        SYNTAX INTEGER(0..2147483647)
        MAX-ACCESS read-create
        STATUS current
        DESCRIPTION
            "Specify match criteria that is a tag for route-map."
        ::= { raisecomRoutePolicyRouteMapNodeEntry 8 }

	raisecomRoutePolicyRouteMapNodeMatchMetric  OBJECT-TYPE
        SYNTAX INTEGER(0..2147483647)
        MAX-ACCESS read-create
        STATUS current
        DESCRIPTION
            "Specify match criteria that is a metric for route-map."
        ::= { raisecomRoutePolicyRouteMapNodeEntry 9 }

	raisecomRoutePolicyRouteMapNodeSetLevel  OBJECT-TYPE
        SYNTAX INTEGER{
					   stub-area(1),
					   backbone (2)
					  }
        MAX-ACCESS read-create
        STATUS current
        DESCRIPTION
            "1 means importing routes into an OSPF NSSA area. 2 means importing routes into an OSPF backbone area."
        ::= { raisecomRoutePolicyRouteMapNodeEntry 10 }

	raisecomRoutePolicyRouteMapNodeSetTag  OBJECT-TYPE
        SYNTAX INTEGER(0..2147483647)
        MAX-ACCESS read-create
        STATUS current
        DESCRIPTION
            "Set tag of route."
        ::= { raisecomRoutePolicyRouteMapNodeEntry 11 }

	raisecomRoutePolicyRouteMapNodeSetMetricRule  OBJECT-TYPE
        SYNTAX INTEGER {
						add       (1),
						subtract  (2)
						}
        MAX-ACCESS read-create
        STATUS current
        DESCRIPTION
            "Set metric rule, add or subtract."
        ::= { raisecomRoutePolicyRouteMapNodeEntry 12 }

	raisecomRoutePolicyRouteMapNodeSetMetric  OBJECT-TYPE
        SYNTAX INTEGER(0..2147483647)
        MAX-ACCESS read-create
        STATUS current
        DESCRIPTION
            "Set metric of route."
        ::= { raisecomRoutePolicyRouteMapNodeEntry 13 }

	raisecomRoutePolicyRouteMapNodeSetMetricType  OBJECT-TYPE
        SYNTAX INTEGER {
						type-1 (1),
						type-2 (2)
					   }
        MAX-ACCESS read-create
        STATUS current
        DESCRIPTION
            "type-1 means OSPF External Type 1 routes,
			type-2 means OSPF External Type 2 routes."
        ::= { raisecomRoutePolicyRouteMapNodeEntry 14 }

	raisecomRoutePolicyRouteMapNodeRowStatus  OBJECT-TYPE
        SYNTAX RowStatus
        MAX-ACCESS read-create
        STATUS current
        DESCRIPTION
            "This object allows entries to be created
			and deleted in the
			raisecomRoutePolicyRouteMapNodeTable."
        ::= { raisecomRoutePolicyRouteMapNodeEntry 15 }


--raisecomRoutePolicyRouteMapStatisticsTable

    raisecomRoutePolicyRouteMapStatisticsTable      OBJECT-TYPE
        SYNTAX   SEQUENCE OF RaisecomRoutePolicyRouteMapStatisticsEntry
        MAX-ACCESS	 not-accessible
        STATUS   current
        DESCRIPTION
                 "IP-Prefix-List Statistics Table"
        ::= { raisecomRoutePolicyRouteMap   4 }

    raisecomRoutePolicyRouteMapStatisticsEntry   OBJECT-TYPE
        SYNTAX RaisecomRoutePolicyRouteMapStatisticsEntry
        MAX-ACCESS not-accessible
        STATUS current
        DESCRIPTION
            "An entry in raisecomRoutePolicyRouteMapStatisticsTable."
        INDEX { raisecomRoutePolicyRouteMapIndex}
        ::= { raisecomRoutePolicyRouteMapStatisticsTable 1 }

    RaisecomRoutePolicyRouteMapStatisticsEntry  ::= SEQUENCE {
        raisecomRoutePolicyRouteMapRefCount          Counter32
        }

    raisecomRoutePolicyRouteMapRefCount  OBJECT-TYPE
        SYNTAX Counter32
        MAX-ACCESS read-only
        STATUS current
        DESCRIPTION
            "The reference count of a route-map."
        ::= { raisecomRoutePolicyRouteMapStatisticsEntry 1 }

--
-- END of RoutePolicy-MIB
--

END
