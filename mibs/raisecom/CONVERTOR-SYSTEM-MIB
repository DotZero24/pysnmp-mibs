--MibName=rcmcSystem
-- =======================================================================
-- Version info
--
-- Version 1.0 Created 2005.07.27 by LONGYANG
-- This version of MIB is created just for the use of Network Management Systems
-- display and set the convertor system configuration.
--
-- Copyright(c) 2002-2005 by RAISECOM TECH, Ltd.
-- =======================================================================



CONVERTOR-SYSTEM-MIB DEFINITIONS ::= BEGIN

	IMPORTS
        MODULE-IDENTITY
                	FROM SNMPv2-SMI
		OBJECT-TYPE
					FROM SNMPv2-SMI
		iscomMediaConvertor
					FROM RAISECOM-BASE-MIB
        PortList,EnableVar
                    FROM SWITCH-TC;

   rcmcSystem MODULE-IDENTITY

        LAST-UPDATED    "200507270000Z"
        ORGANIZATION    "Raisecom Science & Technology Co., ltd"
        CONTACT-INFO    "Raisecom Science & Technology Co., ltd.
                         E-mail: support@raisecom.com"

        DESCRIPTION     "iscom Media Convertor system Enterprise MIB definition."
        ::= { iscomMediaConvertor 1 }


------------------------------------------------------------------------------
--  groups in the convertor system MIB
------------------------------------------------------------------------------
rcmcOamConfig     		OBJECT IDENTIFIER ::= { rcmcSystem 1 }
rcmcPortInfoConfig       OBJECT IDENTIFIER ::= { rcmcSystem 2 }


------------------------------------------------------------------------------
--  Oam configuration group
------------------------------------------------------------------------------
	rcmcOamEnable  OBJECT-TYPE
 	     SYNTAX     EnableVar
         MAX-ACCESS read-write
         STATUS     current
         DESCRIPTION
                " Set OAM to enable(1) or disable(2)."
 	     ::= { rcmcOamConfig 1 }

	rcmcOamWorkMode  OBJECT-TYPE
         SYNTAX		INTEGER
         {
            masterCtrl(1),
        	slaveCtrl(2)
         }
         MAX-ACCESS  read-write
         STATUS      current
         DESCRIPTION
           		" The work mode of the device when OAM is enabled."
        ::= { rcmcOamConfig 2 }

    --Oam configuration trap
    rcmcOamConfigTrap  OBJECT IDENTIFIER ::= { rcmcOamConfig 3 }

    rcmcOamRemoteLostTrap NOTIFICATION-TYPE
			STATUS	current
			DESCRIPTION
			"OAM remote device can not reach."
            ::={rcmcOamConfigTrap 1 }

    rcmcOamRemoteRecoverTrap NOTIFICATION-TYPE
			STATUS	current
			DESCRIPTION
			"OAM remote device exit."
            ::={rcmcOamConfigTrap 2 }


------------------------------------------------------------------------------
--  Port information group
------------------------------------------------------------------------------
    rcmcPortTable  OBJECT-TYPE
			SYNTAX		SEQUENCE OF	RcmcPortEntry
			MAX-ACCESS	not-accessible
			STATUS		current
			DESCRIPTION
				 "A table of port information and associated properties.."
			::=	{  rcmcPortInfoConfig 1 }

	rcmcPortEntry  OBJECT-TYPE
			SYNTAX		RcmcPortEntry
			MAX-ACCESS	not-accessible
			STATUS		current
			DESCRIPTION
			   	"Table entry for port information."
			INDEX {	rcmcPortIndex }
			::=	{ rcmcPortTable 1 }

	RcmcPortEntry ::= SEQUENCE {
			rcmcPortIndex         			INTEGER,
			rcmcPortOptModuleType 			INTEGER,
			rcmcPortFaultPassEnable     	EnableVar,
			rcmcPortFaultPassStatus      	INTEGER,
			rcmcPortSD    	                INTEGER,
			rcmcPortFaultReturnEnable    	EnableVar,
			rcmcPortFaultReturnStatus   	INTEGER,
			rcmcPortFefi					INTEGER,
			rcmcPortFPToPorts               PortList
			}

  	rcmcPortIndex OBJECT-TYPE
 	      	SYNTAX 	  	INTEGER
	      	MAX-ACCESS  read-only
	      	STATUS      current
 	      	DESCRIPTION
           			"An index based 1 that uniquely identifies a port entry."
          	::= { rcmcPortEntry 1 }

    rcmcPortOptModuleType  OBJECT-TYPE
 	      	SYNTAX 	  	INTEGER
       	  	{
      	     	optical-M(1),
      	     	optical-S1(2),
      	     	optical-S2(3),
      	     	optical-S3(4),
      	     	optical-SS13(5),
      	     	optical-SS15(6),
      	     	optical-SS23(7),
      	     	optical-SS25(8),
      	     	optical-SS35(9),
       	  		unknown(10)
      	  	}
	      	MAX-ACCESS  read-only
	      	STATUS      current
 	      	DESCRIPTION
           			"Optical module type."
          	::= { rcmcPortEntry 2 }

    rcmcPortFaultPassEnable OBJECT-TYPE
        	SYNTAX  	EnableVar
        	MAX-ACCESS 	read-write
        	STATUS 		current
        	DESCRIPTION
                	"Set fault pass on the port to enable(1) or disable(2)."
        	DEFVAL  { disable }
        	::= { rcmcPortEntry 3 }

    rcmcPortFaultPassStatus  OBJECT-TYPE
        	SYNTAX INTEGER
      		{
	           normal (1),
	           down (2)
	        }
	        MAX-ACCESS 		read-only
        	STATUS 			current
        	DESCRIPTION
            	"Port state changging result of fault pass.
            	 If normal(1), there is no fault pass occurring.
            	 If down(2), the port is down result of fault pass occurring."
        	::= { rcmcPortEntry 4 }

	rcmcPortSD     OBJECT-TYPE
	        SYNTAX  INTEGER
	        {
	           normal (1),
	           sd (2),
	           unavailable(3)
	        }
	        MAX-ACCESS  read-only
	        STATUS  current
	        DESCRIPTION
	        	  "SD status.
	        	  This value of TP is unavailable."
			::= { rcmcPortEntry 5 }

	rcmcPortFaultReturnEnable  OBJECT-TYPE
        	SYNTAX  	INTEGER
        	{
	           enable (1),
	           disable (2),
	           unavailable(3)
        	}
        	MAX-ACCESS 	read-write
        	STATUS 		current
        	DESCRIPTION
                	"Set fault return on the port to enable(1) or disable(2).
                	This value of TP is unavailable."
        	::= { rcmcPortEntry 6 }

	rcmcPortFaultReturnStatus  OBJECT-TYPE
        	SYNTAX INTEGER {
	           normal (1),
	           down (2),
	           unavailable(3)
        	}
        	MAX-ACCESS 		read-only
        	STATUS 			current
        	DESCRIPTION
            	"Port state changging result of fault return.
            	 If normal(1), there is no fault return occurring.
            	 If down(2), the port is down result of fault return occurring.
            	 This value of TP is unavailable."
        	::= { rcmcPortEntry 7 }

     rcmcPortFefi  OBJECT-TYPE
	        SYNTAX  INTEGER
	        {
	           normal (1),
	           fefi (2),
	           unavailable(3)
	        }
	        MAX-ACCESS  read-only
	        STATUS  current
	        DESCRIPTION
	        	  "The status of FEFI.
	        	  This value of TP is unavailable."
			::= { rcmcPortEntry 8 }

     rcmcPortFPToPorts  OBJECT-TYPE
	        SYNTAX PortList
       		MAX-ACCESS read-write
        	STATUS current
	        DESCRIPTION
	        	  "The destination ports when fault-pass is occured."
			::= { rcmcPortEntry 9 }

	--Port information Trap
    rcmcPortInfoTrap         OBJECT IDENTIFIER ::= { rcmcPortInfoConfig 2 }

    rcmcPortFaultPassTrap  NOTIFICATION-TYPE
			OBJECTS{ rcmcPortIndex, rcmcPortFaultPassStatus }
			STATUS	current
			DESCRIPTION
				"Fault pass has occured on the port identified by rcPortIndex."
            ::={rcmcPortInfoTrap 1 }

    rcmcPortFaultReturnTrap NOTIFICATION-TYPE
			OBJECTS{ rcmcPortIndex, rcmcPortFaultReturnStatus }
			STATUS	current
			DESCRIPTION
				"Fault return has occured on the port identified by rcPortIndex."
            ::={rcmcPortInfoTrap 2 }

    rcmcPortFefiTrap   NOTIFICATION-TYPE
			OBJECTS{ rcmcPortIndex, rcmcPortFefi}
			STATUS	current
			DESCRIPTION
				"Fefi has occured on the port identified by rcPortIndex."
            ::={rcmcPortInfoTrap 3 }

    rcmcPortSDTrap     NOTIFICATION-TYPE
			OBJECTS{ rcmcPortIndex, rcmcPortSD}
			STATUS	current
			DESCRIPTION
				"Fefi has occured on the port identified by rcPortIndex."
            ::={rcmcPortInfoTrap 4 }

END
