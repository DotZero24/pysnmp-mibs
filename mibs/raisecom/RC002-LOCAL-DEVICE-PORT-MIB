-- File: RC002-LOCAL-DEVICE-PORT-MIB.my
-- Changes:
-- author:SunSuli


  RC002-LOCAL-DEVICE-PORT-MIB DEFINITIONS ::= BEGIN

    IMPORTS
		IpAddress, OBJECT-TYPE, MODULE-IDENTITY,
		NOTIFICATION-TYPE, Integer32,Counter32,Unsigned32
                           FROM SNMPv2-SMI
		DisplayString,
		TimeStamp
		           FROM SNMPv2-TC
                rcftChassisIndex, rcftSlotIndex,rcftMibObjects,rcftSlotStat
                           FROM RAISECOM-RCFT-MIB;

    rcftSlotPortMib  MODULE-IDENTITY
	    LAST-UPDATED "1201101431Z"
	    ORGANIZATION "RaiseCom Technology CO.,LTD"
	    CONTACT-INFO
	        "
	       www.raisecom.com
	        "
	    DESCRIPTION
	        "  "

       REVISION      "0901190000Z"
       DESCRIPTION
              "
                rcftEthFxPortStatus 增加对 BIT19和BIT20的定义;
                rcftEthFxPortLoopOrder增加枚举3;
				--by sunying"

       REVISION      "0903170000Z"
       DESCRIPTION
              "
                rcftEthFxPortStatus 增加对 BIT21的定义;
				--by sunying"

       REVISION      "0905140000Z"
       DESCRIPTION
              "
                rcftV35PortAlarmStatus 增加对 BIT12的定义;
				--by wu yanxiong"

	   REVISION      "0905150000Z"
       DESCRIPTION
              "
                rcftE1PortStatus 增加对 BIT19/20的定义;
				--by kuanglili"

	   REVISION      "0905190000Z"
       DESCRIPTION
              "
                rcftEthFxPortModuleType 和 rcftPdhPortModuleType 中取消了ss3(9) 光头类型
                采用公司统一的光头类型(即ss34(9) 、ss35(10))
				--by kuanglili"

 	   REVISION      "0905260000Z"
       DESCRIPTION
              "
				增加了rcftV35PortDSRTrap;
				--by wuyanxiong"

 	   REVISION      "0905271600Z"
       DESCRIPTION
              "
				add rcftEthFxPortSFPType;
				--by xujingru"
       REVISION      "0906091600Z"
       DESCRIPTION
              "
              	add rcftEthFxPortLoopOrder 节点的几个环回命令枚举值
              	add rcftEthFxPortLoopStatus节点的几个环回状态枚举值
				add rcftEthFxPortSFPInfo ;
				--by kuanglili"
   	   REVISION      "0906171600Z"
       DESCRIPTION
              "
				add the value of copperline(15) in rcftEthFxPortTransmitMedia;
				--by wu yanxiong"
   	   REVISION      "0907021600Z"
       DESCRIPTION
              "
				rcftVideoPortStatus 增加双向视频口的特性 BIT3-BIT7
				add rcftVideoPortSignalInLosTrap视频输入信号丢失告警
				    rcftVideoPortSignalOutLosTrap视频输出信号丢失告警
				--by wu yanxiong"
   	   REVISION      "0907171600Z"
       DESCRIPTION
              "
				添加rcftE1DS1PortType,用以在ifTable入库等情况下在E1表中
				区分E1和DS1接口类型。
				--by wu yanxiong"
   	   REVISION      "0908280000Z"
       DESCRIPTION
              "
				1、把rcftE1DS1PortType移置设备级；
				2、添加远端E1接口级mib节点 rcftE1CVCnt；
				3、添加rcftEthFePortRestrictSpeedStep 枚举值
				4、添加rcftE1PortStatus BIT21 网管通道模式 位
				5、rcftE1BertStatus 属性 read-write 和 BIT4： BERT方向
				6、统一各端口命令节点枚举值 1--34
				--by wu yanxiong"
	    REVISION      "0909090000Z"
        DESCRIPTION
              "
				1、增加rcftEthFxPortLOLTrap。
				2、rcftEthFxPortStatus节点中增加对bit22位的定义。
				--by kuanglili
			  "
 	    REVISION      "0909180000Z"
        DESCRIPTION
              "
				增加64位 流量统计节点
				rcftEthFx64RxBytes	Counter64
				rcftEthFx64TxBytes	Counter64
				 --by wuyanxiong
			  "

 	   REVISION      "0909270000Z"
       DESCRIPTION
              "
                rcftEthFxPortModuleType 和 rcftPdhPortModuleType 中
                增加了SFP(15) 光头类型
                参照采用公司统一的光头类型
				--by kuanglili"

        REVISION      "0910300948Z"
        DESCRIPTION
              "
				增加rcftSlotVLANMib表。
				增加 rcftEthFePortPVID rcftEthFePorttag  rcftEthFePortCOS 节点。
				增加 rcftEthFxPortPVID rcftEthFxPorttag  rcftEthFxPortCOS 节点。
					--by kuanglili
			  "
        REVISION   "0912211418Z"
        DESCRIPTION
        	"
        		增加rcftEthFxPortStatus的bit23位定义光口LOS
        		增加rcftEthFxPortLOSTrap告警
        	"
        REVISION      "0912210000Z"
        DESCRIPTION
              "
				根据RCVS1000-601BL等设备的mib编程说明及代码，断定
				rcftVideoPortStatus bit 0 原枚举值有误，更正为
				0：正常；1：告警
									--by wuyanxiong
			  "

        REVISION      "1201101431Z"
        DESCRIPTION
              "
				增加 rcftE1PortAlarmStatus BIT23 对端E-3告警
				0：正常；1：告警
				增加 rcftE1PortTransErrorCodeMoreToR10E-3 告警
									--by yangbintao
			  "



	    ::= { rcftSlotStat 10 }


    rcftEthPortMib OBJECT IDENTIFIER	 ::= {rcftSlotPortMib 1}

    rcftPdhPortMib OBJECT IDENTIFIER	 ::= {rcftSlotPortMib 2}

    rcftE1PortMib  OBJECT IDENTIFIER	 ::= {rcftSlotPortMib 3}

    rcftV35PortMib OBJECT IDENTIFIER	 ::= {rcftSlotPortMib 4}

    rcftSHDSLPortMib OBJECT IDENTIFIER	 ::= {rcftSlotPortMib 5}

    rcftAudioPortMib OBJECT IDENTIFIER	 ::= {rcftSlotPortMib 6}

    rcftDS3E3PortMib OBJECT IDENTIFIER	 ::= {rcftSlotPortMib 7}

    rcftDS1PortMib	OBJECT IDENTIFIER	::={rcftSlotPortMib 8}

    rcftVideoPortMib OBJECT IDENTIFIER ::={rcftSlotPortMib 9}

    rcftDataPortMib	OBJECT IDENTIFIER ::={rcftSlotPortMib 10}

     rcftSimpleModuleMib	OBJECT IDENTIFIER ::={rcftSlotPortMib 11}

     rcftSlotPerformaceMib	OBJECT IDENTIFIER ::={rcftSlotPortMib 12}

     rcftSlotVCGMib		OBJECT IDENTIFIER ::={rcftSlotPortMib 13}

     rcftSlotVLANMib    OBJECT IDENTIFIER ::={rcftSlotPortMib 14}




    -----------------------以太网端口--------------------------------

    rcftEthFxPortMib OBJECT IDENTIFIER	 ::= {rcftEthPortMib 1}

    rcftEthFxPortObjects  OBJECT IDENTIFIER	 ::= {rcftEthFxPortMib 1}
    rcftEthFxPortPerformance OBJECT IDENTIFIER	 ::= {rcftEthFxPortMib 2}
    rcftEthFxPortTraps OBJECT IDENTIFIER	 ::= {rcftEthFxPortMib 10}


    rcftEthFePortMib OBJECT IDENTIFIER	 ::= {rcftEthPortMib 2}

    rcftEthFePortObjects  OBJECT IDENTIFIER	 ::= {rcftEthFePortMib 1}
    rcftEthFePortPerformance OBJECT IDENTIFIER	 ::= {rcftEthFePortMib 2}
    rcftEthFePortTraps OBJECT IDENTIFIER	 ::= {rcftEthFePortMib 10}


    -----------------------PDH光口------------------------------------

    rcftPdhPortObjects  OBJECT IDENTIFIER	 ::= {rcftPdhPortMib 1}
    rcftPdhPortPerformance OBJECT IDENTIFIER	 ::= {rcftPdhPortMib 2}
    rcftPdhPortTraps OBJECT IDENTIFIER	 ::= {rcftPdhPortMib 10}

   --------------------------E1端口------------------------------------

    rcftE1PortObjects  OBJECT IDENTIFIER	 ::= {rcftE1PortMib 1}
    rcftE1PortPerformance OBJECT IDENTIFIER	 ::= {rcftE1PortMib 2}
    rcftE1PortTraps OBJECT IDENTIFIER	 ::= {rcftE1PortMib 10}

   --------------------------V35端口------------------------------------

    rcftV35PortObjects  OBJECT IDENTIFIER	 ::= {rcftV35PortMib 1}
    rcftV35PortPerformance OBJECT IDENTIFIER	 ::= {rcftV35PortMib 2}
    rcftV35PortTraps OBJECT IDENTIFIER	 ::= {rcftV35PortMib 10}

   --------------------------G.端口------------------------------------

    rcftSHDSLPortObjects  OBJECT IDENTIFIER	 ::= {rcftSHDSLPortMib 1}
    rcftSHDSLPortPerformance OBJECT IDENTIFIER	 ::= {rcftSHDSLPortMib 2}
    rcftSHDSLPortTraps OBJECT IDENTIFIER	 ::= {rcftSHDSLPortMib 10}


   --------------------------AUDIO端口------------------------------------

    rcftAudioPortObjects  OBJECT IDENTIFIER	 ::= {rcftAudioPortMib 1}
    rcftAudioPortPerformance OBJECT IDENTIFIER	 ::= {rcftAudioPortMib 2}
    rcftAudioPortTraps OBJECT IDENTIFIER	 ::= {rcftAudioPortMib 10}

   --------------------------DS3 E3端口------------------------------------

    rcftDS3E3PortObjects  OBJECT IDENTIFIER	 ::= {rcftDS3E3PortMib 1}
    rcftDS3E3PortPerformance OBJECT IDENTIFIER	 ::= {rcftDS3E3PortMib 2}
    rcftDS3E3PortTraps OBJECT IDENTIFIER	 ::= {rcftDS3E3PortMib 10}

  --------------------------DS1端口------------------------------------
    rcftDS1PortObjects	OBJECT IDENTIFIER	::={rcftDS1PortMib 1}
    rcftDS1PortPerformance	OBJECT IDENTIFIER	::={rcftDS1PortMib 2}
    rcftDS1PortTraps OBJECT IDENTIFIER	::={rcftDS1PortMib 10}

    -----------------------Video 视频口--------------------------------
    rcftVideoPortObjects OBJECT IDENTIFIER  ::={rcftVideoPortMib 1}
    rcftVideoPortPerformance OBJECT IDENTIFIER ::={rcftVideoPortMib 2}
    rcftVideoPortTraps OBJECT IDENTIFIER ::={rcftVideoPortMib 10}

    ----------------------Data 数据口---------------------------------
    rcftDataPortObjects OBJECT IDENTIFIER ::={rcftDataPortMib 1}
    rcftDataPortPerformance OBJECT IDENTIFIER ::={rcftDataPortMib 2}
    rcftDataPortTraps OBJECT IDENTIFIER ::={rcftDataPortMib 10}

        ----------------------simpleModule 数据口---------------------------------
    rcftSimpleModuleObjects OBJECT IDENTIFIER ::={rcftSimpleModuleMib 1}
    rcftSimpleModulePerformance OBJECT IDENTIFIER ::={rcftSimpleModuleMib 2}
    rcftSimpleModuleTraps OBJECT IDENTIFIER ::={rcftSimpleModuleMib 10}

    ---------------------- FPGA 流量统计 ----------------------
    rcftSlotPerformance OBJECT IDENTIFIER ::={rcftSlotPerformaceMib 1}

    ----------------------VCG MIB-------------------------
    rcftSlotVCGObjects  OBJECT IDENTIFIER ::={rcftSlotVCGMib 1}
    rcftSlotVCGPerformance OBJECT IDENTIFIER ::={rcftSlotVCGMib 2}
    rcftSlotVCGTraps OBJECT IDENTIFIER ::={rcftSlotVCGMib 10}

    ----------------------VLAN MIB-------------------------
    rcftSlotVLANObjects  OBJECT IDENTIFIER ::={rcftSlotVLANMib 1}


   --------------------------以太网光口的对象-----------------------------
    rcftEthFxPortTable OBJECT-TYPE
       SYNTAX  SEQUENCE OF RcftEthFxPortEntry
       MAX-ACCESS  not-accessible
       STATUS  current
       DESCRIPTION
       "
         The EthFx PORT table.
       "
       ::= { rcftEthFxPortObjects 1 }

    rcftEthFxPortEntry OBJECT-TYPE
       SYNTAX  RcftEthFxPortEntry
       MAX-ACCESS  not-accessible
       STATUS  current
       DESCRIPTION
       "
          An entry in the EthFx PORT table.

       "
       INDEX   { rcftChassisIndex, rcftSlotIndex,rcftEthFxPortIndex }
       ::= { rcftEthFxPortTable 1 }

    RcftEthFxPortEntry ::=
       SEQUENCE {
       rcftEthFxPortIndex		 	Integer32,
       rcftEthFxPortStatus			INTEGER,
       rcftEthFxPortModuleMaxSpeed INTEGER,
       rcftEthFxPortConnectorType INTEGER,
       rcftEthFxPortTransmitMedia INTEGER,
       rcftEthFxPortModuleWaveLen INTEGER,
       rcftEthFxPortModuleManufacturer OCTET STRING,
       rcftEthFxPortModuleDescr OCTET STRING,
       rcftEthFxPortModuleVersion OCTET STRING,
       rcftEthFxPortModuleSerialNumber OCTET STRING,
       rcftEthFxPortModuleType INTEGER,
       rcftEthFxPortRxRestrictSpeed	INTEGER,
       rcftEthFxPortTxRestrictSpeed	INTEGER,
       rcftEthFxPortRestrictSpeedStep INTEGER,
       rcftEthFxPortLoopOrder	INTEGER,
       rcftEthFxPortLoopStatus  INTEGER,
       rcftEthFxPortSFPDiagnoInfo INTEGER,
       rcftEthFxPortSFPDiagnoAlarmStatus INTEGER,
       rcftEthFxPortSFPDiagnoWarningStatus INTEGER,
       rcftEthFxPortTranDistance INTEGER,
       rcftEthFxPortSFPType INTEGER,
       rcftEthFxPortSFPInfo INTEGER,
       rcftEthFxPortPVID	INTEGER,
       rcftEthFxPorttag		INTEGER,
       rcftEthFxPortCOS		INTEGER
       }


    rcftEthFxPortIndex OBJECT-TYPE
    	SYNTAX	   Integer32
    	MAX-ACCESS read-only
    	STATUS		current
    	DESCRIPTION
    	"
    		EthFx口的索引
    	"
        ::= { rcftEthFxPortEntry 1 }

    rcftEthFxPortStatus OBJECT-TYPE
    	SYNTAX		INTEGER
    	MAX-ACCESS	read-write
    	STATUS		current
    	DESCRIPTION
    	"
      bit23：光口LOS告警					1:恢复    0：告警
      bit22：光口LOL告警。				    1：恢复    0：告警
      Bit21：以太网光口OAM网管。			1：使能；  0：禁止。
      Bit20：LBK-Test-OK（Bit19为1时有效）。1：环回测试成功，0：环回测试失败
      Bit19：LBK-Test_Valid。1：环回测试过， 0：没有进行过环回测试
      Bit18：远端掉电。1：掉电， 0：未掉电
      Bit17：发送使能。1：使能， 0：禁止
      Bit16：流量控制。1：使能， 0：禁止
      Bit15：与bit3 bit2 配合使用表示EthFx端口的状态
      		bit15 bit3 bit2
      		000：光口开
      		001：光口关
      		010：因本端故障转移关
      		011：因ALS关
      		100：因环回关

      Bit14：激光管灵敏度：1：异常，0：正常
      Bit13：激光管发送功率：1：异常，0：正常
      Bit12：激光管工作状态：1：异常，0：正常
      Bit11：远端xx端口故障向光口转移：1：使能，0：禁止
      Bit10：本地xx端口故障向光口转移：1：使能，0：禁止
      Bit9：光口SD信号：1：有效，0：无效
      Bit8：光口双工：1：全双工，0：半双工
      Bit7-6：光口速率：00：10M， 01：100M，
      		  10：1000M， 11：保留
      Bit5：光口自协商：1：使能，0：禁止
      Bit4：ALS功能：1：打开，0：禁止
      Bit3-2：光口使能：00：开启，01：关闭，
      		  10：光口因为电口故障关，11：光口因为无光收信号关
      Bit1：接口Link状态： 1：Linkup，0：Linkdown
      Bit0：模块不在位通知Exist：1：在位，0：不在位
    	"
 		::= { rcftEthFxPortEntry 2 }

 		rcftEthFxPortModuleMaxSpeed OBJECT-TYPE
      SYNTAX INTEGER
      {
        stm16(1),
        stm8(2),
        stm4(3),
        stm1(4)
      }
      MAX-ACCESS read-only
      STATUS current
      DESCRIPTION
      "
       	SFP模块接口模块的最大速率:(1 : 2.5Gbit/s;
       	                    2 : 1.25Gbit/s;
       	                    3 : 622Mbit/s;
       	                    4 : 155Mbit/s
       	                    5 : 125Mbit/s)
      "
    ::={ rcftEthFxPortEntry 3 }

    rcftEthFxPortConnectorType OBJECT-TYPE
      SYNTAX INTEGER
      {
        unkkown(1),
        rj45(2),
        sc(3),
        style1(4),
        style2(5),
        bnctnc(6),
        coaheader(7),
        jack(8),
        lc(9),
        mtrj(10),
        mu(11),
        sg(12),
        opticalpigtail(13),
        hssdc2(14),
        copperpigtail(15)

      }
      MAX-ACCESS read-only
      STATUS current
      DESCRIPTION
      "
       	SFP模块连接头类型:(1 : 未知类型;
       	                   2 : rj45;
       	                   3 : sc;
       	                   4 : style1;
       	                   5 : style2;
       	                   6 : bnctnc;
       	                   7 : coaheader;
       	                   8 : jack;
       	                   9 : lc;
       	                   10 : mtrj;
       	                   11 : mu;
       	                   12 : sg;
       	                   13 : opticalpigtail;
       	                   14 : hssdc2;
       	                   15 : copperpigtail)
      "
    ::={ rcftEthFxPortEntry 4 }

    rcftEthFxPortTransmitMedia OBJECT-TYPE
      SYNTAX INTEGER
      {
        unkkown(1),
        singleMode9um(2),
        multiMode50um(3),
        multiMode62point5um(4),
        copperline(15)

      }
      MAX-ACCESS read-only
      STATUS current
      DESCRIPTION
      "
       	SFP模块传输介质:(1 : 未知类型;
       	                 2 : 单模9um;
       	                 3 : 多模50um;
       	                 4 : 多模62.5um
       	                 15：铜线)
      "
    ::={ rcftEthFxPortEntry 5 }

    rcftEthFxPortModuleWaveLen OBJECT-TYPE
      SYNTAX INTEGER
      MAX-ACCESS read-only
      STATUS current
      DESCRIPTION
      "
       	SFP模块工作波长(单位为nm)
      "
    ::={rcftEthFxPortEntry 6}

    rcftEthFxPortModuleManufacturer  OBJECT-TYPE
      SYNTAX OCTET STRING(SIZE (0..30))
      MAX-ACCESS read-only
      STATUS current
      DESCRIPTION
      "
       SFP模块的模块制造厂商
      "
    ::={rcftEthFxPortEntry 7}

    rcftEthFxPortModuleDescr OBJECT-TYPE
      SYNTAX OCTET STRING(SIZE (0..30))
      MAX-ACCESS read-only
      STATUS current
      DESCRIPTION
      "
        SFP模块的产品型号
      "
    ::={rcftEthFxPortEntry 8}

    rcftEthFxPortModuleVersion OBJECT-TYPE
      SYNTAX OCTET STRING(SIZE (0..10))
      MAX-ACCESS read-only
      STATUS current
      DESCRIPTION
      "
        SFP模块的版本号
      "
    ::={rcftEthFxPortEntry 9}

    rcftEthFxPortModuleSerialNumber OBJECT-TYPE
      SYNTAX OCTET STRING(SIZE (0..30))
      MAX-ACCESS read-only
      STATUS current
      DESCRIPTION
      "
        SFP模块的序列号
      "
    ::={rcftEthFxPortEntry 10}

    rcftEthFxPortModuleType  OBJECT-TYPE
      SYNTAX INTEGER
      {
      	 optical-M(1),
      	 optical-S1(2),
      	 optical-S2(3),
      	 optical-S3(4),
      	 optical-SS13(5),
      	 optical-SS15(6),
      	 optical-SS23(7),
      	 optical-SS25(8),
      	 --optical-SS3(9),  kuanglili 20090519 根据公司规范取消ss3光头类型
      	 optical-SS34(9),
      	 optical-SS35(10),
      	 optical-S15(12),  --kuanglili 20090909 S15光模块类型枚举值为12
      	 optical_SFP(15),
      	 unknown-type(100)
      }
      MAX-ACCESS read-only
      STATUS current
      DESCRIPTION
      "
      	 以太网光口的光模块类型
      "
	::= { rcftEthFxPortEntry 11 }

 	rcftEthFxPortRxRestrictSpeed  OBJECT-TYPE
    	SYNTAX		INTEGER
    	MAX-ACCESS	read-write
    	STATUS		current
    	DESCRIPTION
    	"
             接收带宽
    	"
 	::= { rcftEthFxPortEntry 12 }

 	rcftEthFxPortTxRestrictSpeed  OBJECT-TYPE
    	SYNTAX		INTEGER
    	MAX-ACCESS	read-write
    	STATUS		current
    	DESCRIPTION
    	"
           发送带宽
       	"
 	::= { rcftEthFxPortEntry 13 }

 	rcftEthFxPortRestrictSpeedStep	OBJECT-TYPE
 		SYNTAX	INTEGER
 		MAX-ACCESS	read-only
 		STATUS		current
 		DESCRIPTION
 		"
 			带宽粒度
 			0x00：64Kbps；0x01：32Kbps（无）；其余：保留。
 		"
 	::= { rcftEthFxPortEntry 14 }

 	rcftEthFxPortLoopOrder	OBJECT-TYPE
 	     SYNTAX	INTEGER
 	     {
 	     	ethFxinsideLoopEnable(1),
 	     	ethFxinsideLoopDisable(2),
 	     	ethFxLoopbackTest(3)
 	     }
 	     MAX-ACCESS	read-write
 		 STATUS		current
 		 DESCRIPTION
 		 "
 		   光口环回命令:
 		   	1:本地内环环回使能，
 		   	2:本地内环环回禁止 ,
 		   	3:环回检测（一次完成自动停止）
 		   	4:远端外环使能
 		   	5：远端外环禁止
 		   	6：OAM环使能
 		   	7：OAM环禁止

 		 "
 	::= { rcftEthFxPortEntry 15 }

 	rcftEthFxPortLoopStatus		OBJECT-TYPE
 	     SYNTAX	INTEGER
 	     {
 	     	ethFxPortoutsideLoop(1),
 	     	ethFxPortnormal(100)
 	     }
 	     MAX-ACCESS	read-only
 	     STATUS		current
         DESCRIPTION
         "
            光口环回:
            	1: 光口本地外环
            	2：光口远端外环
       		3：光口本地内环
            	4：OAM环

            	100:正常
         "
 	::= { rcftEthFxPortEntry 16 }

 	rcftEthFxPortSFPDiagnoInfo	OBJECT-TYPE
  		 SYNTAX	INTEGER
  		 MAX-ACCESS 	read-only
  		 STATUS	current
  		 DESCRIPTION
  		 "
     		局端模块数字诊断的相关信息
    		bit3: 监测到sfp模块         1：有告警   0：无
     		bit2: 采用内部校准：  		1：有效，  	0：无效
      		bit1: 采用外部校准：  		1：有效，  	0：无效
     		bit0: 是否具有数字诊断功能：1：有 		0：无
  		 "
 	     ::={rcftEthFxPortEntry 17}

 	 rcftEthFxPortSFPDiagnoAlarmStatus	OBJECT-TYPE
  		 SYNTAX	INTEGER
  		 MAX-ACCESS 	read-only
  		 STATUS	current
  		 DESCRIPTION
  		 "
     		局端模块数字诊断的相关告警

            bit9: 收光功率下限告警：  	1：有告警，0：没有告警
     		bit8: 收光功率上限告警：  	1：有告警，0：没有告警
     		bit7: 发光功率下限告警：  	1：有告警，0：没有告警
     		bit6: 发光功率上限告警：  	1：有告警，0：没有告警
     		bit5: 电流下限告警：  		1：有告警，0：没有告警
     		bit4: 电流上限告警：  		1：有告警，0：没有告警
     		bit3: 电压下限告警：  		1：有告警，0：没有告警
     		bit2: 电压上限告警：  		1：有告警，0：没有告警
     		bit1: 温度下限告警：  		1：有告警，0：没有告警
     		bit0: 温度上限告警：  		1：有告警，0：没有告警

 	     "
 	     ::={rcftEthFxPortEntry 18}

 	  rcftEthFxPortSFPDiagnoWarningStatus   OBJECT-TYPE
  		 SYNTAX	INTEGER
  		 MAX-ACCESS 	read-only
  		 STATUS	current
  		 DESCRIPTION
  		 "
     		局端模块数字诊断的相关警告

            bit9: 收光功率下限警告：  	1：有警告，0：没有警告
     		bit8: 收光功率上限警告：  	1：有警告，0：没有警告
     		bit7: 发光功率下限警告：  	1：有警告，0：没有警告
     		bit6: 发光功率上限警告：  	1：有警告，0：没有警告
     		bit5: 电流下限警告：  		1：有警告，0：没有警告
     		bit4: 电流上限警告：  		1：有警告，0：没有警告
     		bit3: 电压下限警告：  		1：有警告，0：没有警告
     		bit2: 电压上限警告：  		1：有警告，0：没有警告
     		bit1: 温度下限警告：  		1：有警告，0：没有警告
     		bit0: 温度上限警告：  		1：有警告，0：没有警告
          "
 	     ::={rcftEthFxPortEntry 19}

 	   rcftEthFxPortTranDistance    OBJECT-TYPE
  		 SYNTAX	INTEGER
  		 MAX-ACCESS 	read-only
  		 STATUS	current
  		 DESCRIPTION
  		 "
     		SFP光模块的传输距离，单位为km。
         "
         ::={rcftEthFxPortEntry 20}

    rcftEthFxPortSFPType    OBJECT-TYPE
  		 SYNTAX	INTEGER
  		 {
 	     	utp(1),
 	     	fiber(2)
 	     }
  		 MAX-ACCESS 	read-only
  		 STATUS	current
  		 DESCRIPTION
  		 "
     		SFP接口类型，1：eth电口，2：eth光口。
         "
         ::={rcftEthFxPortEntry 21}

      rcftEthFxPortSFPInfo    OBJECT-TYPE
  		 SYNTAX	INTEGER
  		 MAX-ACCESS 	read-only
  		 STATUS	current
  		 DESCRIPTION
  		 "
     		SFP 光模块信息

     		Bit2：局端SFP模块光口打开使能：		1：打开，0：关闭
			Bit1：局端SFP模块激光器发送失效：	1：正常，0：失效
			Bit0：局端SFP模块输入信号丢失： 	1：正常，0：丢失
         "
         ::={rcftEthFxPortEntry 22}

      rcftEthFxPortPVID	OBJECT-TYPE
    	SYNTAX INTEGER
    	MAX-ACCESS read-write
    	STATUS current
    	DESCRIPTION
    	"
    		1~4094
    	"
    	::={ rcftEthFxPortEntry 23}

       rcftEthFxPorttag		OBJECT-TYPE
    	SYNTAX INTEGER
    	MAX-ACCESS read-write
    	STATUS current
    	DESCRIPTION
    	"
    		1：tag， 2：untag
       	"
    	::={ rcftEthFxPortEntry 24}

       rcftEthFxPortCOS		OBJECT-TYPE
    	SYNTAX INTEGER
    	MAX-ACCESS read-write
    	STATUS current
    	DESCRIPTION
    	"
    		0~7
    	"
    	::={ rcftEthFxPortEntry 25}

   --------------------------以太网光口的流量统计--------------------------

      rcftEthFxStatisticTable OBJECT-TYPE
	        SYNTAX SEQUENCE OF RcftEthFxStatisticEntry
	        MAX-ACCESS not-accessible
	        STATUS current
	        DESCRIPTION
	          "
	          局端设备EthFx端口的统计表.
	          "
            ::= {rcftEthFxPortPerformance 1}

	    rcftEthFxStatisticEntry OBJECT-TYPE
	        SYNTAX RcftEthFxStatisticEntry
	        MAX-ACCESS not-accessible
	        STATUS current
	        DESCRIPTION
	          "
	             以rcftEthFxIndex为索引
	          "
	        AUGMENTS { rcftEthFxPortEntry }
	        ::= {rcftEthFxStatisticTable 1}

	    RcftEthFxStatisticEntry ::= SEQUENCE {
				rcftEthFxTxPackets         Counter32,
				rcftEthFxRxPackets         Counter32,
				rcftEthFxTxErrPackets		Counter32,
				rcftEthFxRxErrPackets		Counter32,
				rcftEthFxFluxTimer		   Counter32,
				rcftEthFxRxBytes	Counter32,
				rcftEthFxTxBytes	Counter32,
				rcftEthFx64RxBytes	Counter64,
				rcftEthFx64TxBytes	Counter64
	      }


    	  rcftEthFxTxPackets OBJECT-TYPE
					SYNTAX Counter32
					MAX-ACCESS read-only
					STATUS current
					DESCRIPTION
						"
							2GEM-X发送以太网包数
						"
					::= { rcftEthFxStatisticEntry 1 }

		 rcftEthFxRxPackets OBJECT-TYPE
					SYNTAX Counter32
					MAX-ACCESS read-only
					STATUS current
					DESCRIPTION
						"
							2GEM-X接收以太网包数
						"
					::= { rcftEthFxStatisticEntry 2 }

		rcftEthFxTxErrPackets	OBJECT-TYPE
					SYNTAX Counter32
					MAX-ACCESS read-only
					STATUS current
					DESCRIPTION
						"
							2GEM-X发送以错误太网包数
						"
					::= { rcftEthFxStatisticEntry 3}
		rcftEthFxRxErrPackets 	OBJECT-TYPE
					SYNTAX Counter32
					MAX-ACCESS read-only
					STATUS current
					DESCRIPTION
						"
							2GEM-X接收以错误太网包数
						"
					::= { rcftEthFxStatisticEntry 4}


     rcftEthFxFluxTimer	OBJECT-TYPE
        	SYNTAX		Counter32
        	MAX-ACCESS 	read-only
        	STATUS		current
        	DESCRIPTION
        		"
        			流量统计的时间
        		"
          ::= { rcftEthFxStatisticEntry 5 }

     rcftEthFxRxBytes   OBJECT-TYPE
		SYNTAX Counter32
		MAX-ACCESS read-only
		STATUS current
		DESCRIPTION
		"
			接收以太网字节数
		"
		::= { rcftEthFxStatisticEntry 6 }

	 rcftEthFxTxBytes   OBJECT-TYPE
		SYNTAX Counter32
		MAX-ACCESS read-only
		STATUS current
		DESCRIPTION
		"
			发送以太网字节数
		"
		::= { rcftEthFxStatisticEntry 7 }

     rcftEthFx64RxBytes   OBJECT-TYPE
		SYNTAX Counter64
		MAX-ACCESS read-only
		STATUS current
		DESCRIPTION
		"
			接收以太网字节数,取值范围0 至 2的64次方-1
		"
		::= { rcftEthFxStatisticEntry 8 }

	 rcftEthFx64TxBytes   OBJECT-TYPE
		SYNTAX Counter64
		MAX-ACCESS read-only
		STATUS current
		DESCRIPTION
		"
			发送以太网字节数，取值范围0 至 2的64次方-1
		"
		::= { rcftEthFxStatisticEntry 9 }



   --------------------------以太网光口的告警--------------------------

       rcftEthFxPortLinkTrap	NOTIFICATION-TYPE
      	OBJECTS{
			rcftEthFxPortStatus
      	}
      	STATUS current
     	DESCRIPTION
     	"
     		局端设备上以太网光口的LINK告警
     	"
     	::= { rcftEthFxPortTraps 1 }

     	rcftEthFxPortExitTrap   NOTIFICATION-TYPE
     	 OBJECTS{
     	 	rcftEthFxPortStatus
     	 }
     	 STATUS current
     	 DESCRIPTION
     	 "
     	 	局端设备上以太网光口在位告警
     	 "
     	 ::= { rcftEthFxPortTraps 2}

     	rcftEthFxPortTempHighTrap  NOTIFICATION-TYPE
    	OBJECTS{
     	 	rcftEthFxPortSFPDiagnoAlarmStatus
     	 }
     	STATUS current
    	DESCRIPTION
    	"
    		SFP模块温度上限告警
    	"
        ::= { rcftEthFxPortTraps 3 }

      rcftEthFxPortTempLowTrap  NOTIFICATION-TYPE
    	OBJECTS{
     	 	rcftEthFxPortSFPDiagnoAlarmStatus
     	 }
    	STATUS current
    	DESCRIPTION
    	"
    		SFP模块温度下限告警
    	"
        ::= { rcftEthFxPortTraps 4 }

      rcftEthFxPortVoltageHighTrap  NOTIFICATION-TYPE
    	OBJECTS{
     	 	rcftEthFxPortSFPDiagnoAlarmStatus
     	 }
    	STATUS current
    	DESCRIPTION
    	"
    		SFP模块电压上限告警
    	"
        ::= { rcftEthFxPortTraps 5 }

      rcftEthFxPortVoltageLowTrap  NOTIFICATION-TYPE
    	OBJECTS{
     	 	rcftEthFxPortSFPDiagnoAlarmStatus
     	 }     	STATUS current
    	DESCRIPTION
    	"
    		SFP模块电压下限告警
    	"
        ::= { rcftEthFxPortTraps 6 }

      rcftEthFxPortOffsetCurrHighTrap  NOTIFICATION-TYPE
    	OBJECTS{
     	 	rcftEthFxPortSFPDiagnoAlarmStatus
     	 }
    	STATUS current
    	DESCRIPTION
    	"
    		SFP模块电流上限告警
    	"
        ::= { rcftEthFxPortTraps 7 }

      rcftEthFxPortOffsetCurrLowTrap  NOTIFICATION-TYPE
    	OBJECTS{
     	 	rcftEthFxPortSFPDiagnoAlarmStatus
     	 }
    	STATUS current
    	DESCRIPTION
    	"
    		SFP模块电流下限告警
    	"
        ::= { rcftEthFxPortTraps 8 }

      rcftEthFxPortSendPowerHighTrap  NOTIFICATION-TYPE
    	OBJECTS{
     	 	rcftEthFxPortSFPDiagnoAlarmStatus
     	 }
    	STATUS current
    	DESCRIPTION
    	"
    		SFP模块发光功率上限告警
    	"
        ::= { rcftEthFxPortTraps 9 }

      rcftEthFxPortSendPowerLowTrap  NOTIFICATION-TYPE
    	OBJECTS{
     	 	rcftEthFxPortSFPDiagnoAlarmStatus
     	 }
    	STATUS current
    	DESCRIPTION
    	"
    		SFP模块发光功率下限告警
    	"
        ::= { rcftEthFxPortTraps 10 }

      rcftEthFxPortRecvPowerHighTrap  NOTIFICATION-TYPE
    	OBJECTS{
     	 	rcftEthFxPortSFPDiagnoAlarmStatus
     	 }
    	STATUS current
    	DESCRIPTION
    	"
    		SFP模块收光功率上限告警
    	"
        ::= { rcftEthFxPortTraps 11 }

      rcftEthFxPortRecvPowerLowTrap  NOTIFICATION-TYPE
    	OBJECTS{
     	 	rcftEthFxPortSFPDiagnoAlarmStatus
     	 }
    	STATUS current
    	DESCRIPTION
    	"
    		SFP模块收光功率下限告警
    	"
        ::= { rcftEthFxPortTraps 12 }

     	rcftEthFxPortTempHighWarningTrap  NOTIFICATION-TYPE
    	OBJECTS{
     	 	rcftEthFxPortSFPDiagnoWarningStatus
     	 }
     	STATUS current
    	DESCRIPTION
    	"
    		SFP模块温度上限警告
    	"
        ::= { rcftEthFxPortTraps 13 }

      rcftEthFxPortTempLowWarningTrap  NOTIFICATION-TYPE
    	OBJECTS{
     	 	rcftEthFxPortSFPDiagnoWarningStatus
     	 }
    	STATUS current
    	DESCRIPTION
    	"
    		SFP模块温度下限警告
    	"
        ::= { rcftEthFxPortTraps 14 }

      rcftEthFxPortVoltageHighWarningTrap  NOTIFICATION-TYPE
    	OBJECTS{
     	 	rcftEthFxPortSFPDiagnoWarningStatus
     	 }
    	STATUS current
    	DESCRIPTION
    	"
    		SFP模块电压上限警告
    	"
        ::= { rcftEthFxPortTraps 15 }

      rcftEthFxPortVoltageLowWarningTrap  NOTIFICATION-TYPE
    	OBJECTS{
     	 	rcftEthFxPortSFPDiagnoWarningStatus
     	 }     	STATUS current
    	DESCRIPTION
    	"
    		SFP模块电压下限警告
    	"
        ::= { rcftEthFxPortTraps 16 }

      rcftEthFxPortOffsetCurrHighWarningTrap  NOTIFICATION-TYPE
    	OBJECTS{
     	 	rcftEthFxPortSFPDiagnoWarningStatus
     	 }
    	STATUS current
    	DESCRIPTION
    	"
    		SFP模块电流上限警告
    	"
        ::= { rcftEthFxPortTraps 17 }

      rcftEthFxPortOffsetCurrLowWarningTrap  NOTIFICATION-TYPE
    	OBJECTS{
     	 	rcftEthFxPortSFPDiagnoWarningStatus
     	 }
    	STATUS current
    	DESCRIPTION
    	"
    		SFP模块电流下限警告
    	"
        ::= { rcftEthFxPortTraps 18 }

      rcftEthFxPortSendPowerHighWarningTrap  NOTIFICATION-TYPE
    	OBJECTS{
     	 	rcftEthFxPortSFPDiagnoWarningStatus
     	 }
    	STATUS current
    	DESCRIPTION
    	"
    		SFP模块发光功率上限警告
    	"
        ::= { rcftEthFxPortTraps 19 }

      rcftEthFxPortSendPowerLowWarningTrap  NOTIFICATION-TYPE
    	OBJECTS{
     	 	rcftEthFxPortSFPDiagnoWarningStatus
     	 }
    	STATUS current
    	DESCRIPTION
    	"
    		SFP模块发光功率下限警告
    	"
        ::= { rcftEthFxPortTraps 20 }

      rcftEthFxPortRecvPowerHighWarningTrap  NOTIFICATION-TYPE
    	OBJECTS{
     	 	rcftEthFxPortSFPDiagnoWarningStatus
     	 }
    	STATUS current
    	DESCRIPTION
    	"
    		SFP模块收光功率上限警告
    	"
        ::= { rcftEthFxPortTraps 21 }

      rcftEthFxPortRecvPowerLowWarningTrap  NOTIFICATION-TYPE
    	OBJECTS{
     	 	rcftEthFxPortSFPDiagnoWarningStatus
     	 }
    	STATUS current
    	DESCRIPTION
    	"
    		SFP模块收光功率下限警告
    	"
        ::= { rcftEthFxPortTraps 22 }

      rcftEthFxPortSDTrap  NOTIFICATION-TYPE
    	OBJECTS{
     	 	rcftEthFxPortStatus
     	 }
    	STATUS current
    	DESCRIPTION
    	"
    		SFP模块收光功率下限警告
    	"
        ::= { rcftEthFxPortTraps 23 }

        rcftEthFxPortRemotePowerDownTrap  NOTIFICATION-TYPE
    	OBJECTS{
     	 	rcftEthFxPortStatus
     	 }
    	STATUS current
    	DESCRIPTION
    	"
    		远端收发器掉电告警
    	"
        ::= { rcftEthFxPortTraps 24 }

        rcftEthFxPortLaserTxfaultTrap  NOTIFICATION-TYPE
    	OBJECTS{
     	 	rcftEthFxPortSFPInfo
     	 }
    	STATUS current
    	DESCRIPTION
    	"
    		激光器发送失效告警。1：恢复，2：告警
    	"
        ::= { rcftEthFxPortTraps 25 }

        rcftEthFxPortInputSignalLosTrap  NOTIFICATION-TYPE
    	OBJECTS{
     	 	rcftEthFxPortSFPInfo
     	 }
    	STATUS current
    	DESCRIPTION
    	"
    		sfp输入信号丢失。1：恢复，2：告警
    	"
        ::= { rcftEthFxPortTraps 26 }

        rcftEthFxPortLOLTrap  NOTIFICATION-TYPE
    	OBJECTS{
     	 	rcftEthFxPortStatus
     	 }
    	STATUS current
    	DESCRIPTION
    	"
    		信号失锁。1：恢复，2：告警
    	"
        ::= { rcftEthFxPortTraps 27 }

        rcftEthFxPortLOSTrap  NOTIFICATION-TYPE
    	OBJECTS{
     	 	rcftEthFxPortStatus
     	 }
    	STATUS current
    	DESCRIPTION
    	"
    		信号丢失。1：恢复，2：告警
    	"
        ::= { rcftEthFxPortTraps 28 }



   --------------------------以太网电口的对象-----------------------------
    rcftEthFePortTable OBJECT-TYPE
       SYNTAX  SEQUENCE OF RcftEthFePortEntry
       MAX-ACCESS  not-accessible
       STATUS  current
       DESCRIPTION
       "
         The EthFe PORT table.
       "
       ::= { rcftEthFePortObjects 1 }

    rcftEthFePortEntry OBJECT-TYPE
       SYNTAX  RcftEthFePortEntry
       MAX-ACCESS  not-accessible
       STATUS  current
       DESCRIPTION
       "
          An entry in the EthFe PORT table.

       "
       INDEX   { rcftChassisIndex, rcftSlotIndex,rcftEthFePortIndex }
       ::= { rcftEthFePortTable 1 }


    RcftEthFePortEntry ::=
       SEQUENCE {
       rcftEthFePortIndex		 	Integer32,
       rcftEthFePortStatus			INTEGER,
       rcftEthFePortRxRestrictSpeed	INTEGER,
       rcftEthFePortTxRestrictSpeed	INTEGER,
       rcftEthFePortRestrictSpeedStep INTEGER,
       rcftEthFePortOrder INTEGER,
       rcftEthFePortPosition INTEGER,
       rcftEthFePortPVID	INTEGER,
       rcftEthFePorttag		INTEGER,
       rcftEthFePortCOS		INTEGER
       }

    rcftEthFePortIndex OBJECT-TYPE
    	SYNTAX	   Integer32
    	MAX-ACCESS read-only
    	STATUS		current
    	DESCRIPTION
    	"
    		EthFe口的索引
    	"
        ::= { rcftEthFePortEntry 1 }

    rcftEthFePortStatus OBJECT-TYPE
    	SYNTAX		INTEGER
    	MAX-ACCESS	read-write
    	STATUS		current
    	DESCRIPTION
    	"
    		BIT18：与bit15 bit4 配合使用表示EthFe的状态
    			bit18 bit15 bit14
    			000：电口开
    			001：电口关
    			010：因本端故障转移关
    			011：因对端故障转移关
    			100：因环回关

    		BIT17-16:  带宽粒度	0x00：64Kbps；0x01：32Kbps（无）；其余：保留。

			BIT15-14: Port_En 	00：电口开；01：电口关；10：电口因为G口故障关； 11：因为远端电口故障关。
			BIT13:    LOC_FP_EN  1：使能本地其它端口故障向电口转移；   0：禁止。
			BIT12:    REM_FP_EN  1：使能远端电口故障向电口转移；  0：禁止。
			BIT11-10: MDIX_Valid 00：电口允许自交叉且工作于SW方式；01：电口允许自交叉且工作于NIC方式；10：电口禁止自交叉，设置工作于SW方式；11：电口禁止自交叉。设置工作于NIC方式。
			BIT9-8:   保留	固定00'b。

			BIT7:  保留	固定0'b。
			BIT6:    Flow_ Control  1：以太网口流控功能打开； 0：以太网口流控功能关闭。
			BIT5:    Port_Sel  0：Fx                 1：Tx
			BIT4:    Link	0：电口Link Down；       1：电口Link Up。
			BIT3:    Auto_En 0：电口自协商禁止；     1：电口自协商使能。
			BIT2-1:  SPD	00：电口速率为10M；      01：电口速率为100M；10：电口速率为1000M（无）； 11：保留。
			BIT0:    FDX	0：电口工作于半双工方式；1：电口工作于全双工。
    	"
 		::= { rcftEthFePortEntry 2 }

 	rcftEthFePortRxRestrictSpeed  OBJECT-TYPE
    	SYNTAX		INTEGER
    	MAX-ACCESS	read-write
    	STATUS		current
    	DESCRIPTION
    	"
             接收带宽
    	"
 		::= { rcftEthFePortEntry 3 }

 	rcftEthFePortTxRestrictSpeed  OBJECT-TYPE
    	SYNTAX		INTEGER
    	MAX-ACCESS	read-write
    	STATUS		current
    	DESCRIPTION
    	"
           发送带宽
       	"
 		::= { rcftEthFePortEntry 4 }

 	rcftEthFePortRestrictSpeedStep	OBJECT-TYPE
 		SYNTAX	INTEGER
 		MAX-ACCESS	read-only
 		STATUS		current
 		DESCRIPTION
 		"
 			带宽粒度
 			0x00：64Kbps；0x01：32Kbps（无）；
 			2：80Kbps;
			3：800Kbps;
			4：8000Kbps;
			其余：保留。
 		"
 	    ::= { rcftEthFePortEntry 5 }

	rcftEthFePortOrder	OBJECT-TYPE
		SYNTAX	INTEGER
		MAX-ACCESS	read-write
		STATUS	current
		DESCRIPTION
		"
			    1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
 				22: 端口BERT测试开始
 				23: 端口BERT测试结束
				24：统计信息清零
				25：告警屏蔽
				26：告警屏蔽解除
				27：端口未用支路告警屏蔽
				28：端口未用支路告警屏蔽解除
				29：环回检测使能
				30：环回检测停止
				31：开始查询SFP扩展信息
				32；停止查询SFP扩展信息
				33：开始查询SFP数字诊断信息
				34：停止查询SFP数字诊断信息
				注：31-34尚没有对网管开放


			注意：对于约定5，枚举值5-9废弃，
			rcftEthFePortOrder的枚举值要和其他接口级命令节点始终保持完全一致。
		"
		::= { rcftEthFePortEntry 6 }

		 rcftEthFePortPosition OBJECT-TYPE
    	SYNTAX INTEGER
    	MAX-ACCESS read-only
    	STATUS current
    	DESCRIPTION
    	"
    		eth 口的位置信息：
    		bit7-4：盘
    		bit3-0：槽
    	"
    	::={ rcftEthFePortEntry 7}

    	rcftEthFePortPVID	OBJECT-TYPE
    	SYNTAX INTEGER
    	MAX-ACCESS read-write
    	STATUS current
    	DESCRIPTION
    	"
    		1~4094
    	"
    	::={ rcftEthFePortEntry 8}

       rcftEthFePorttag		OBJECT-TYPE
    	SYNTAX INTEGER
    	MAX-ACCESS read-write
    	STATUS current
    	DESCRIPTION
    	"
    		1：tag， 2：untag
       	"
    	::={ rcftEthFePortEntry 9}

       rcftEthFePortCOS		OBJECT-TYPE
    	SYNTAX INTEGER
    	MAX-ACCESS read-write
    	STATUS current
    	DESCRIPTION
    	"
    		0~7
    	"
    	::={ rcftEthFePortEntry 10}


    --------------------------以太网电口的流量统计--------------------------

         rcftEthFeStatisticTable OBJECT-TYPE
	        SYNTAX SEQUENCE OF RcftEthFeStatisticEntry
	        MAX-ACCESS not-accessible
	        STATUS current
	        DESCRIPTION
	          "
	          局端设备Eth端口的统计表.
	          "
            ::= {rcftEthFePortPerformance 1}

	    rcftEthFeStatisticEntry OBJECT-TYPE
	        SYNTAX RcftEthFeStatisticEntry
	        MAX-ACCESS not-accessible
	        STATUS current
	        DESCRIPTION
	          "
	             以rcftEthFeIndex为索引
	          "
	        AUGMENTS { rcftEthFePortEntry }
	        ::= {rcftEthFeStatisticTable 1}

	    RcftEthFeStatisticEntry ::= SEQUENCE {
				rcftEthFeTxPackets         Counter32,
				rcftEthFeTxBytes           Counter32,
				rcftEthFeTxFailurePackets  Counter32,
				rcftEthFeRxPackets         Counter32,
				rcftEthFeRxBytes           Counter32,
				rcftEthFeRxErrorPackets    Counter32,
				rcftEthFeFluxTimer		   Counter32
	         }


    	  rcftEthFeTxPackets OBJECT-TYPE
					SYNTAX Counter32
					MAX-ACCESS read-only
					STATUS current
					DESCRIPTION
						"
							以太网口发送以太网包数
						"
					::= { rcftEthFeStatisticEntry 1 }

		 rcftEthFeTxBytes OBJECT-TYPE
					SYNTAX Counter32
					MAX-ACCESS read-only
					STATUS current
					DESCRIPTION
						"
							以太网口发送以太网字节数
						"
					::= { rcftEthFeStatisticEntry 2 }


	    rcftEthFeTxFailurePackets OBJECT-TYPE
					SYNTAX Counter32
					MAX-ACCESS read-only
					STATUS current
					DESCRIPTION
						"
							以太网电口发送以太网丢包数
						"
					::= { rcftEthFeStatisticEntry 3 }

		 rcftEthFeRxPackets OBJECT-TYPE
					SYNTAX Counter32
					MAX-ACCESS read-only
					STATUS current
					DESCRIPTION
						"
							以太网口接收以太网包数
						"
					::= { rcftEthFeStatisticEntry 4 }

		 rcftEthFeRxBytes OBJECT-TYPE
					SYNTAX Counter32
					MAX-ACCESS read-only
					STATUS current
					DESCRIPTION
						"
							以太网口接收以太网字节数
						"
					::= { rcftEthFeStatisticEntry 5 }

	    rcftEthFeRxErrorPackets OBJECT-TYPE
					SYNTAX Counter32
					MAX-ACCESS read-only
					STATUS current
					DESCRIPTION
						"
							以太网电口接收以太网丢包数
						"
					::= { rcftEthFeStatisticEntry 6 }

        rcftEthFeFluxTimer	OBJECT-TYPE
        			SYNTAX		Counter32
        			MAX-ACCESS 	read-only
        			STATUS		current
        			DESCRIPTION
        				"
        					流量统计的时间
        				"
                    ::= { rcftEthFeStatisticEntry 7 }


    --------------------------以太网电口的告警--------------------------

       rcftEthFePortLinkTrap	NOTIFICATION-TYPE
      	OBJECTS{
			rcftEthFePortStatus
      	}
      	STATUS current
     	DESCRIPTION
     	"
     		局端设备上以太网电口的LINK告警
     	"
     	::= { rcftEthFePortTraps 1 }

   --------------------------PDH端口的对象---------------------------------

    rcftPdhPortTable OBJECT-TYPE
       SYNTAX  SEQUENCE OF RcftPdhPortEntry
       MAX-ACCESS  not-accessible
       STATUS  current
       DESCRIPTION
       "
         The Pdh PORT table.
       "
       ::= { rcftPdhPortObjects 1 }

    rcftPdhPortEntry OBJECT-TYPE
       SYNTAX  RcftPdhPortEntry
       MAX-ACCESS  not-accessible
       STATUS  current
       DESCRIPTION
       "
          An entry in the Pdh PORT table.

       "
       INDEX   { rcftChassisIndex, rcftSlotIndex,rcftPdhPortIndex }
       ::= { rcftPdhPortTable 1 }


    RcftPdhPortEntry ::=
       SEQUENCE {
       rcftPdhPortIndex		 	Integer32,
       rcftPdhPortAlarmStatus	INTEGER,
       rcftPdhPortStatus		INTEGER,
       rcftPdhPortECSCnt		INTEGER,
       rcftPdhPortSECSCnt       INTEGER,
       rcftPdhPortModuleType	INTEGER,
       rcftPdhPortLoopStatus    INTEGER,
       rcftPdhPortOrder		INTEGER,
       rcftPdhPortBertStatus	INTEGER,
       rcftPdhPortBertErrCode	Unsigned32
       }

    rcftPdhPortIndex OBJECT-TYPE
    	SYNTAX	   Integer32
    	MAX-ACCESS read-only
    	STATUS		current
    	DESCRIPTION
    	"
    		Pdh口的索引
    	"
        ::= { rcftPdhPortEntry 1 }

     rcftPdhPortAlarmStatus OBJECT-TYPE
     	SYNTAX	INTEGER
     	MAX-ACCESS read-only
     	STATUS	current
    	DESCRIPTION
    	"
    		Pdh口的告警状态
    		其他位：保留
			BIT20	从本地设备上查看到的对端设备掉电告警	 0：告警； 1：正常
			BIT19	从本地设备上查看到的对端设备光口的E-6	 0：告警； 1：正常
			BIT18	从本地设备上查看到的对端设备光口的E-3	 0：告警； 1：正常
			BIT17	从本地设备上查看到的对端设备光口的LOF	 0：告警； 1：正常
			BIT16	从本地设备上查看到的对端设备光口的LOS	 0：告警； 1：正常

			BIT3	E-6 pdh光口的E-6告警 0：告警； 1：正常
			BIT2	E-3	pdh光口的E-3告警 0：告警； 1：正常
			BIT1    LOF pdh光口LOF告警   0：告警   1：正常
			BIT0    LOS pdh光口LOS告警   0：告警   1：正常
		"
        ::= { rcftPdhPortEntry 2 }

     rcftPdhPortStatus OBJECT-TYPE
     	SYNTAX	INTEGER
     	MAX-ACCESS read-write
     	STATUS	current
    	DESCRIPTION
    	"
    		Pdh口的状态
    		其他位：保留
    		BIT10  光口故障转移           0：禁止   1：使能
			BIT9   光口所接的对端设备的掉电告警	 0：告警； 1：正常
			BIT8   光口ALS开关设置    	0:禁止       1: 使能
            BIT7-6 光口的环回状态 0：无环回，1：内环，2：外环 3：双向环
			BIT5   光口ALS    	0:禁止       1: 使能
			BIT4   从本地设备上查看到的对端设备光口的工作状态 0:不工作     1：工作
			BIT3   光口的工作状态 0:不工作     1：工作

			BIT2-1 光口因故障转移功能使能时的开关状态：
			       0：开
			       1：因电-光Faultpass功能使能时关闭
			       2：因光口ALS功能使能关闭
		    BIT0   光口的打开关闭：1:open, 0:close

    	"
        ::= { rcftPdhPortEntry 3 }

     rcftPdhPortECSCnt	OBJECT-TYPE
     	SYNTAX	INTEGER
     	MAX-ACCESS	read-only
     	STATUS	current
     	DESCRIPTION
     	"
     		pdh光口误码秒
     	"
     	::= { rcftPdhPortEntry 4 }

     rcftPdhPortSECSCnt	OBJECT-TYPE
     	SYNTAX	INTEGER
     	MAX-ACCESS	read-only
     	STATUS	current
     	DESCRIPTION
     	"
     		pdh光口严重误码秒
     	"
     	::= { rcftPdhPortEntry 5 }


     rcftPdhPortModuleType  OBJECT-TYPE
      	  SYNTAX INTEGER
      	  {
      	     optical-M(1),
      	     optical-S1(2),
      	     optical-S2(3),
      	     optical-S3(4),
      	     optical-SS13(5),
      	     optical-SS15(6),
      	     optical-SS23(7),
      	     optical-SS25(8),
      	     --optical-SS3(9),    kuanglili 20090519 根据公司规范取消ss3光头类型
      	     optical-SS34(9),
      	     optical-SS35(10),
      	     optical-S15(12),   --kuanglili 20090909 S15光模块类型枚举值为12
      	     optical-SFP(15),
      	     optical-SS24(23),
 	         optical-S1FC(50),
 	         optical-S1A(51),
 	         optical-S2A(52),
 	         optical-S3A(53),
      	     unknown-type(100)
      	  }
      	  MAX-ACCESS read-only
      	  STATUS current
      	  DESCRIPTION
      	  "
      	    远端设备pdh光口的光模块类型
      	  "
          ::= { rcftPdhPortEntry 6 }

    rcftPdhPortLoopStatus	OBJECT-TYPE
     	SYNTAX	INTEGER
     	MAX-ACCESS	read-only
     	STATUS	current
     	DESCRIPTION
     	"
     		pdh光口环回状态
     		1:本地环回，2：无本地环回，3：远端环回，4：无远端环回，
 			5:无环回，
 			6：本地内环使能，7：本地外环使能，8：本地双向环使能，
 			9:远端内环使能，10：远端外环使能，11：远端双向环使能，
 			12：本地内环禁止，13:本地外环禁止，14：本地双向环禁止，
 			15：远端内环禁止，16：远端外环禁止，17：远端双向环禁止，
     	"
     	::= { rcftPdhPortEntry 7 }

    rcftPdhPortOrder	OBJECT-TYPE
    	SYNTAX	INTEGER
    	MAX-ACCESS	read-write
    	STATUS	current
    	DESCRIPTION
    	"
			    1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
 				22: 端口BERT测试开始
 				23: 端口BERT测试结束
				24：统计信息清零
				25：告警屏蔽
				26：告警屏蔽解除
				27：端口未用支路告警屏蔽
				28：端口未用支路告警屏蔽解除
				29：环回检测使能
				30：环回检测停止
				31：开始查询SFP扩展信息
				32；停止查询SFP扩展信息
				33：开始查询SFP数字诊断信息
				34：停止查询SFP数字诊断信息
				注：31-34尚没有对网管开放


			注意：对于约定5，枚举值5-9废弃，
		    rcftPdhPortOrder的枚举值要和其他接口级命令节点始终保持完全一致。
		    "
    	::= { rcftPdhPortEntry 8 }

  	rcftPdhPortBertStatus    OBJECT-TYPE
    	SYNTAX	INTEGER
    	MAX-ACCESS	read-only
    	STATUS	current
    	DESCRIPTION
    	"
    	  bit0：1：误码仪使能		0：误码仪禁止
    	"
        ::= { rcftPdhPortEntry 9 }

	rcftPdhPortBertErrCode		OBJECT-TYPE
	    SYNTAX	Unsigned32
	    MAX-ACCESS	read-only
	    STATUS	current
	    DESCRIPTION
	    "
	      误码率方式:误码数，单位是bit
	    "
	    ::= {rcftPdhPortEntry 10}


    rcftPdhPortLOSTrap	NOTIFICATION-TYPE
      	OBJECTS{
			rcftPdhPortAlarmStatus
      	}
      	STATUS current
     	DESCRIPTION
     	"
     		局端设备上Pdh光口的LOS告警
     	"
     	::= { rcftPdhPortTraps 1 }

     rcftPdhPortLOFTrap	NOTIFICATION-TYPE
      	OBJECTS{
			rcftPdhPortAlarmStatus
      	}
      	STATUS current
     	DESCRIPTION
     	"
     		局端设备上Pdh光口的LOF告警
     	"
     	::= { rcftPdhPortTraps 2 }

     rcftPdhPortE3Trap	NOTIFICATION-TYPE
      	OBJECTS{
			rcftPdhPortAlarmStatus
      	}
      	STATUS current
     	DESCRIPTION
     	"
     		局端设备上Pdh光口的E-3告警
     	"
     	::= { rcftPdhPortTraps 3 }


     rcftPdhPortE6Trap	NOTIFICATION-TYPE
      	OBJECTS{
			rcftPdhPortAlarmStatus
      	}
      	STATUS current
     	DESCRIPTION
     	"
     		局端设备上Pdh光口的E-6告警
     	"
     	::= { rcftPdhPortTraps 4 }


    rcftPdhPortToRLOSTrap	NOTIFICATION-TYPE
      	OBJECTS{
			rcftPdhPortAlarmStatus
      	}
      	STATUS current
     	DESCRIPTION
     	"
     		从本地设备上查看到的对端设备光口的LOS告警
     	"
     	::= { rcftPdhPortTraps 5 }

     rcftPdhPortToRLOFTrap	NOTIFICATION-TYPE
      	OBJECTS{
			rcftPdhPortAlarmStatus
      	}
      	STATUS current
     	DESCRIPTION
     	"
     		从本地设备上查看到的对端设备光口的LOF告警
     	"
     	::= { rcftPdhPortTraps 6 }

     rcftPdhPortToRE3Trap	NOTIFICATION-TYPE
      	OBJECTS{
			rcftPdhPortAlarmStatus
      	}
      	STATUS current
     	DESCRIPTION
     	"
     		从本地设备上查看到的对端设备光口的E-3告警
     	"
     	::= { rcftPdhPortTraps 7 }


     rcftPdhPortToRE6Trap	NOTIFICATION-TYPE
      	OBJECTS{
			rcftPdhPortAlarmStatus
      	}
      	STATUS current
     	DESCRIPTION
     	"
     		从本地设备上查看到的对端设备光口的E-6告警
     	"
     	::= { rcftPdhPortTraps 8 }


     rcftPdhPortToRPowerDown	NOTIFICATION-TYPE
      	OBJECTS{
			rcftPdhPortAlarmStatus
      	}
      	STATUS current
     	DESCRIPTION
     	"
     		从本地设备上查看到的对端设备掉电告警
     	"
     	::= { rcftPdhPortTraps 9 }


   --------------------------E1端口的对象---------------------------------

    rcftE1PortTable OBJECT-TYPE
       SYNTAX  SEQUENCE OF RcftE1PortEntry
       MAX-ACCESS  not-accessible
       STATUS  current
       DESCRIPTION
       "
         The E1 PORT table.
       "
       ::= { rcftE1PortObjects 1 }

    rcftE1PortEntry OBJECT-TYPE
       SYNTAX  RcftE1PortEntry
       MAX-ACCESS  not-accessible
       STATUS  current
       DESCRIPTION
       "
          An entry in the E1 PORT table.

       "
       INDEX   { rcftChassisIndex, rcftSlotIndex,rcftE1PortIndex }
       ::= { rcftE1PortTable 1 }


    RcftE1PortEntry ::=
       SEQUENCE {
       rcftE1PortIndex		 	Integer32,
       rcftE1PortAlarmStatus	INTEGER,
       rcftE1PortStatus			INTEGER,
       rcftE1TimeSlots			INTEGER,
       rcftE1TS0Mode			INTEGER,
       rcftE1IdleCode			INTEGER,
       rcftE1LoopStatus			INTEGER,
       rcftE1Order				INTEGER,
       rcftE1PortType			INTEGER,
       rcftE1BertStatus			INTEGER,
	   rcftE1BertTime			Unsigned32,
	   rcftE1BertErrCode		Unsigned32,
	   rcftE1BertUnusedTime		Unsigned32,
	   rcftE1BertPortSpeed		Unsigned32,
	   rcftE1BertCodeType		INTEGER,
	   rcftE1BertCodeNum		INTEGER,
	   rcftE1AlarmRejest 		INTEGER,
	   rcfT1PortAlarmStatus		INTEGER,
	   rcftE1PortVCGNumber		INTEGER,
	   rcftE1PortErrorRate		INTEGER,
	   rcftE1PortESCont         INTEGER,
	   rcftE1PortSESCont        INTEGER,
	   rcftE1PortToRNumber      INTEGER,
	   rcftE1CVCnt			    INTEGER
       }

    rcftE1PortIndex OBJECT-TYPE
    	SYNTAX	   Integer32
    	MAX-ACCESS read-only
    	STATUS		current
    	DESCRIPTION
    	"
    		E1口的索引
    	"
        ::= { rcftE1PortEntry 1 }

     rcftE1PortAlarmStatus OBJECT-TYPE
     	SYNTAX	INTEGER
     	MAX-ACCESS read-only
     	STATUS	current
    	DESCRIPTION
    	"
    		E1口的告警状态
    		其他位：保留

    		Bit23	从本地设备上看到的对端设备E1的E-3告警			0：告警； 1：正常
    		Bit22 	从本地设备上看到的对端设备E1的信号劣化TSD告警  	0：告警   1：正常
    		BIT21  	从本地设备上看到的对端设备E1的CRC告警：			0：告警； 1：正常。
    		BIT20  	从本地设备上看到的对端设备E1的LOMF告警：		0：告警； 1：正常。
    		BIT19  	从本地设备上看到的对端设备E1的LOF告警：			0：告警； 1：正常。
    		BIT18  	从本地设备上看到的对端设备E1的CV告警：			0：告警； 1：正常。
    		BIT17  	从本地设备上看到的对端设备E1的AIS告警：			0：告警； 1：正常。
    		BIT16  	从本地设备上看到的对端设备E1的LOS告警：			0：告警； 1：正常。

            bit7：	RDI，0: 远端缺陷告警。     1: 正常
    		Bit6 	TSD  0：本地E1信号劣化告警 1：本地E1信号正常
    		BIT5	CRC  0: 本地E1 CRC告警；   1：本地E1 CRC正常；
			BIT4	LOMF 0：本地E1 复帧失步；  1：本地E1 复帧正常。
			BIT3	LOF	 0：本地E1 帧失步；	   1：本地E1 帧正常。
			BIT2	CV	 0：本地HDB3 编码违例；1：本地HDB3 编码正常。
			BIT1	AIS	 0：本地AIS 告警；     1：无本地AIS 告警。
			BIT0	LOS	 0：本地信号消失告警； 1：本地信号正常。
    	"
        ::= { rcftE1PortEntry 2 }

     rcftE1PortStatus OBJECT-TYPE
     	SYNTAX	INTEGER
     	MAX-ACCESS read-write
     	STATUS	current
    	DESCRIPTION
    	"
    		E1口的状态
    		其他位：保留
    		BIT21	网管通道模式	 0：不启用	   1：启用独立时隙
    		BIT20	E1环回检测结果	 0：无环	   1：有环
    		BIT19	E1环回检测		 0: 禁止	   1：使能
    		BIT18   E1协议版本       0：V2         1：V3     （网管只用来做逻辑，不显示）
			BIT17	请求时隙跟随	 0：禁止	1：使能
			BIT16	对端跟随         0：无响应，1：响应
    		BIT15-14 EX_LBK-Test  00：没有进行过外环测试； 01：保留；10：外环测试成功；11：外环测试失败。
    		BIT13-12 IN_LBK-Test  00：没有进行过内环测试； 01：保留；10：内环测试成功；11：内环测试失败。
    		BIT11    IDLE_MODE 0：固定使用IDLE_CODE；   1：返回。
    		BIT10-9 PORTTYPE  00：BNC；                01：RJ45插座；    其他：保留
    		BIT8-7  BALANCE	  00：75欧姆非平衡；       01：120欧姆平衡； 其他：保留
			BIT6    SABIT	  0：本地E1 未使用SA BIT； 1：本地E1 使用SA BIT；
			BIT5    PCM31     0：本地E1 PCM30模式；	   1：本地E1 PCM31模式；
			BIT4    FRAME     0：本地E1透明模式；      1：本地E1成帧模式；
			BIT3    CRCAUTO   0: 本地E1 CRC自协商使能  1：禁止
			BIT2    CRC       0：本地CRC未使能；       1：本地CRC使能。
			BIT1    HDB3      0: 本地E1码型NRZ；       1: 本地E1码型HDB3；
			BIT0    OPEN      0：本地E1端口关闭；      1：本地E1端口打开；
    	"
        ::= { rcftE1PortEntry 3 }

      rcftE1TimeSlots  OBJECT-TYPE
      	SYNTAX	INTEGER
      	MAX-ACCESS  read-write
      	STATUS	current
      	DESCRIPTION
      	"
      		E1口在成帧模式下所占用的时隙,bit0-bit30每位分别表示时隙1到时隙31的占用情况。
      		时隙0的占用与否是通过透明成帧模式判断的。
      	"
        ::= { rcftE1PortEntry 4 }

      rcftE1TS0Mode  OBJECT-TYPE
      	SYNTAX  INTEGER
      	MAX-ACCESS read-write
      	STATUS	current
      	DESCRIPTION
		"
			工作模式（TS0）：
			1000：工作于透明模式，透传TS0-32，TS0=1；
			0001：成帧模式0，发送端不发送TS0、接收端重新计算整个TS0；
			1001：成帧模式1，发送端透传TS0、接收端也使用透传来的TS0（IDLE CODE一致时才可以使用此模式）；
			0010：成帧模式2，发送端不发送TS0、接收端返回TS0（CRC除外，重新计算）；
			1010：成帧模式3，发送端透传TS0、但接收端丢弃CRC使用重新计算的CRC；其它：保留。
		"
        ::= { rcftE1PortEntry 5 }

      rcftE1IdleCode OBJECT-TYPE
      	SYNTAX  INTEGER
      	MAX-ACCESS read-write
      	STATUS	current
      	DESCRIPTION
		"
           未用时隙的码字
		"
        ::= { rcftE1PortEntry 6 }

       rcftE1LoopStatus  OBJECT-TYPE
       	SYNTAX	INTEGER
       	{
       		  localDoubleLoopEnable(1),
       		  localDoubleLoopDisable(2),
       		  remoteDoubleLoopEnable(3),
       		  remoteDoubleLoopDisable(4)
       	}
       	MAX-ACCESS read-only
       	STATUS	current
       	DESCRIPTION
       	"
       	     E1的环回状态：1:本地环回，2：无本地环回，3：远端环回，4：无远端环回，
						   5:无环回，
						   6：本地内环使能，7：本地外环使能，8：本地双向环使能，
						   9:远端内环使能，10：远端外环使能，11：远端双向环使能，
						   12：本地内环禁止，13:本地外环禁止，14：本地双向环禁止，
						   15：远端内环禁止，16：远端外环禁止，17：远端双向环禁止，
       	"
        ::= { rcftE1PortEntry 7 }

		rcftE1Order	OBJECT-TYPE
			SYNTAX	INTEGER
			MAX-ACCESS	read-write
			STATUS	current
			DESCRIPTION
			"
			    1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
 				22: 端口BERT测试开始
 				23: 端口BERT测试结束
				24：统计信息清零
				25：告警屏蔽
				26：告警屏蔽解除
				27：端口未用支路告警屏蔽
				28：端口未用支路告警屏蔽解除
				29：环回检测使能
				30：环回检测停止
				31：开始查询SFP扩展信息
				32；停止查询SFP扩展信息
				33：开始查询SFP数字诊断信息
				34：停止查询SFP数字诊断信息
				注：31-34尚没有对网管开放


			注意：对于约定5，枚举值5-9废弃，
			rcftE1Order的枚举值要和其他接口级命令节点始终保持完全一致。
			"
		::= { rcftE1PortEntry 8 }

		rcftE1PortType	OBJECT-TYPE
			SYNTAX	INTEGER
			MAX-ACCESS	read-only
			STATUS	current
			DESCRIPTION
			"
			    表示E1的类型。这个节点主要是针对约定四而增加，用来区分多种E1子块
			    下各个E1的具体类型。

			    1：既可以为成帧，又可为非成帧（对应约定四中的0x10-0x04子块）
				2：非成帧（对应约定四中的0x10-0x06子块）
			"
		::= { rcftE1PortEntry 9 }

	    rcftE1BertStatus		OBJECT-TYPE
	    	SYNTAX  INTEGER
	    	MAX-ACCESS	read-write
	    	STATUS	current
	    	DESCRIPTION
	    	"
	    	  BIT4			BERT方向：		0：线路侧； 1：客户侧
	    	  BIT3			BERT_STATUS		0:正常工作；	1:正在bert
	    	  BIT2-1		BERT_RESULT     00:未测试      01:测试正常；	10:测试失败
	    	  BIT0			BERT_TYPE   	0:误码率方式；  1:误码时间方式
	    	"
	    	::= {rcftE1PortEntry 10}

	    rcftE1BertTime		OBJECT-TYPE
	    	SYNTAX	Unsigned32
	    	MAX-ACCESS	read-only
	    	STATUS	current
	    	DESCRIPTION
	    	"
	    	误码率方式:测试时间，时间随测试的进行而增长,单位 S.
	    	"
	    	::= {rcftE1PortEntry  11}

	    rcftE1BertErrCode		OBJECT-TYPE
	    	SYNTAX	Unsigned32
	    	MAX-ACCESS	read-only
	    	STATUS	current
	    	DESCRIPTION
	    	"
	    	 误码率方式:误码数，单位是bit
	    	"
	    	::= {rcftE1PortEntry 12}

	    rcftE1BertUnusedTime		OBJECT-TYPE
	    	SYNTAX	Unsigned32
	    	MAX-ACCESS	read-only
	    	STATUS	current
	    	DESCRIPTION
	    	"
	    	 误码率方式:测试不可用时间，超过255秒后维持255秒不变，单位是S.
	    	"
	    	::= {rcftE1PortEntry 13}

	    rcftE1BertPortSpeed		OBJECT-TYPE
	    	SYNTAX	Unsigned32
	    	MAX-ACCESS	read-only
	    	STATUS	current
	    	DESCRIPTION
	    	"
	    	 误码率方式:测试的端口速率，单位：kbps。
	    	"
	    	::= {rcftE1PortEntry 14}

	    rcftE1BertCodeType		OBJECT-TYPE
	   		SYNTAX INTEGER
	   		MAX-ACCESS	read-write
	   		STATUS	current
	   		DESCRIPTION
	   		"
	   		误码率方式:测试码型，最大值为127
	   		0000001'b：2的15次方-1；
			其它：保留。

	   		"
	   		::= {rcftE1PortEntry 15}

	    rcftE1BertCodeNum		OBJECT-TYPE
	   		SYNTAX INTEGER
	   		MAX-ACCESS	read-write
	   		STATUS	current
	   		DESCRIPTION
	   		"
	   		误码率方式:测试码数
	   		0010001'b：2的31次方个码；
			0010010'b：2的28次方个码；
			0010011'b：2的25次方个码；
			0010100'b：2的21次方个码；
			0100001'b：测试不停；
			其它：保留。

	   		"
	   		::= {rcftE1PortEntry 16}

	   rcftE1AlarmRejest 		OBJECT-TYPE
	   		SYNTAX INTEGER
	   		MAX-ACCESS	read-only
	   		STATUS	current
	   		DESCRIPTION
	   		"
	   			本地E1 告警屏蔽
	   			 1：屏蔽
	   			 2：不屏蔽
	   		"
	   		::= {rcftE1PortEntry 17}

	   rcfT1PortAlarmStatus		OBJECT-TYPE
	   		SYNTAX INTEGER
	   		MAX-ACCESS	read-only
	   		STATUS	current
	   		DESCRIPTION
	   		"
	   			本地T1的告警
	   			bit1：AIS		0：告警，1：正常
	   			bit0：LOS		0：告警，1：正常

	   		"
	   		::= {rcftE1PortEntry 18}

	   	rcftE1PortVCGNumber   OBJECT-TYPE
	   		SYNTAX INTEGER
	   		MAX-ACCESS	read-only
	   		STATUS	current
	   		DESCRIPTION
	   		"
	   			接口属于哪个VCG成员。
					0：不是VCG成员。
					1~N：表示属与哪个VCG成员。
	   		"
	   		::= {rcftE1PortEntry 19}

	   	rcftE1PortErrorRate  OBJECT-TYPE
	   		SYNTAX INTEGER
	   		MAX-ACCESS	read-only
	   		STATUS	current
	   		DESCRIPTION
	   		"
	   			E1的误码率

	   			1：无误码
	   			2：大于e-6
	   			3：大于e-3
	   		"
	   		::= {rcftE1PortEntry 20}


	   	rcftE1PortESCont   OBJECT-TYPE
	   		SYNTAX INTEGER
	   		MAX-ACCESS	read-only
	   		STATUS	current
	   		DESCRIPTION
	   		"
	   			E1的误码秒

	   		"
	   		::= {rcftE1PortEntry 21}

	   	rcftE1PortSESCont   OBJECT-TYPE
	   		SYNTAX INTEGER
	   		MAX-ACCESS	read-only
	   		STATUS	current
	   		DESCRIPTION
	   		"
	   			E1的严重误码秒
	   		"
	   		::= {rcftE1PortEntry 22}
        rcftE1PortToRNumber   OBJECT-TYPE
	   		SYNTAX INTEGER
	   		MAX-ACCESS	read-only
	   		STATUS	current
	   		DESCRIPTION
	   		"
	   			对端E1编号。
	   		"
	   		::= {rcftE1PortEntry 23}

        rcftE1CVCnt   OBJECT-TYPE
	   		SYNTAX INTEGER
	   		MAX-ACCESS	read-only
	   		STATUS	current
	   		DESCRIPTION
	   		"
	   			E1编码违例统计。	0~65535，累加值，非读清
	   		"
	   		::= {rcftE1PortEntry 24}


       --------------------------E1端口的告警--------------------------

       rcftE1PortLOSTrap	NOTIFICATION-TYPE
      	OBJECTS{
			rcftE1PortAlarmStatus
      	}
      	STATUS current
     	DESCRIPTION
     	"
     		局端设备上E1接口的LOS告警
     	"
     	::= { rcftE1PortTraps 1 }

       rcftE1PortAISTrap	NOTIFICATION-TYPE
      	OBJECTS{
			rcftE1PortAlarmStatus
      	}
      	STATUS current
     	DESCRIPTION
     	"
     		局端设备上E1接口的AIS告警
     	"
     	::= { rcftE1PortTraps 2 }


       rcftE1PortCVTrap	NOTIFICATION-TYPE
      	OBJECTS{
			rcftE1PortAlarmStatus
      	}
      	STATUS current
     	DESCRIPTION
     	"
     		局端设备上E1接口的CV告警
     	"
     	::= { rcftE1PortTraps 3 }

       rcftE1PortLOFTrap	NOTIFICATION-TYPE
      	OBJECTS{
			rcftE1PortAlarmStatus
      	}
      	STATUS current
     	DESCRIPTION
     	"
     		局端设备上E1接口的LOF告警
     	"
     	::= { rcftE1PortTraps 4 }


       rcftE1PortLOMFTrap	NOTIFICATION-TYPE
      	OBJECTS{
			rcftE1PortAlarmStatus
      	}
      	STATUS current
     	DESCRIPTION
     	"
     		局端设备上E1接口的LOMF告警
     	"
     	::= { rcftE1PortTraps 5 }

       rcftE1PortCRCTrap	NOTIFICATION-TYPE
      	OBJECTS{
			rcftE1PortAlarmStatus
      	}
      	STATUS current
     	DESCRIPTION
     	"
     		局端设备上E1接口的CRC告警
     	"
     	::= { rcftE1PortTraps 6 }

       rcftE1PortToRLOSTrap	NOTIFICATION-TYPE
      	OBJECTS{
			rcftE1PortAlarmStatus
      	}
      	STATUS current
     	DESCRIPTION
     	"
     		从本地设备上看到的对端设备E1的LOS告警
     	"
     	::= { rcftE1PortTraps 7 }

     	rcftT1PortLOSTrap     NOTIFICATION-TYPE
      	OBJECTS{
			rcfT1PortAlarmStatus
      	}
      	STATUS current
     	DESCRIPTION
     	"
     		本地设备的T1 LOS告警
       	"
     	::= { rcftE1PortTraps 8 }

     	rcftT1PortAISTrap     NOTIFICATION-TYPE
      	OBJECTS{
			rcfT1PortAlarmStatus
      	}
      	STATUS current
     	DESCRIPTION
     	"
     		本地设备的T1 AIS告警
       	"
     	::= { rcftE1PortTraps 9 }

     	rcftE1PortTSDTrap NOTIFICATION-TYPE
      	OBJECTS{
			rcfT1PortAlarmStatus
      	}
      	STATUS current
     	DESCRIPTION
     	"
     		本地设备的E1 信号恶化告警 ，1：恢复，2：告警。
       	"
     	::= { rcftE1PortTraps 10 }

		rcftE1PortTransErrorCodeMore10E-3 NOTIFICATION-TYPE
      	OBJECTS{
			rcftE1PortErrorRate
      	}
      	STATUS current
     	DESCRIPTION
     	"
     		本地设备的E1 E-3告警   ，1：恢复，2：告警。
       	"
       	::= { rcftE1PortTraps 11 }

		rcftE1PortTransErrorCodeMore10E-6  NOTIFICATION-TYPE
      	OBJECTS{
			rcftE1PortErrorRate
      	}
      	STATUS current
     	DESCRIPTION
     	"
     		本地设备的E1 E-6告警   ，1：恢复，2：告警。
       	"
        ::= { rcftE1PortTraps 12 }

        rcftE1PortRDITrap  NOTIFICATION-TYPE
      	OBJECTS{
			rcfT1PortAlarmStatus
      	}
      	STATUS current
     	DESCRIPTION
     	"
     		设备的RDI告警，当对端设备出现LOS、AIS、LOF任何一个时，本地报RDI告警。
     		1：恢复，2：告警。
       	"
        ::= { rcftE1PortTraps 13 }

		rcftE1PortToRAISTrap  NOTIFICATION-TYPE
      	OBJECTS{
			rcfT1PortAlarmStatus
      	}
      	STATUS current
     	DESCRIPTION
     	"
     		对端E1 AIS告警 ，1：恢复，2：告警。
       	"
        ::= { rcftE1PortTraps 14 }

		rcftE1PortToRLOFTrap  NOTIFICATION-TYPE
      	OBJECTS{
			rcfT1PortAlarmStatus
      	}
      	STATUS current
     	DESCRIPTION
     	"
     		对端E1 LOF告警，1：恢复，2：告警。
       	"
        ::= { rcftE1PortTraps 15 }

		rcftE1PortToRCRCTrap  NOTIFICATION-TYPE
      	OBJECTS{
			rcfT1PortAlarmStatus
      	}
      	STATUS current
     	DESCRIPTION
     	"
     		对端E1 CRC告警，1：恢复，2：告警。
       	"
        ::= { rcftE1PortTraps 16 }

		rcftE1PortToRTSDTrap  NOTIFICATION-TYPE
      	OBJECTS{
			rcfT1PortAlarmStatus
      	}
      	STATUS current
     	DESCRIPTION
     	"
     		对端E1 TSD告警，1：恢复，2：告警。
       	"
        ::= { rcftE1PortTraps 17 }

        rcftE1PortToRLOMFTrap  NOTIFICATION-TYPE
      	OBJECTS{
			rcfT1PortAlarmStatus
      	}
      	STATUS current
     	DESCRIPTION
     	"
     		对端E1 LOMF告警，1：恢复，2：告警。
       	"
        ::= { rcftE1PortTraps 18 }

 		rcftE1PortTransErrorCodeMoreToR10E-3  NOTIFICATION-TYPE
      	OBJECTS{
			rcftE1PortAlarmStatus
      	}
      	STATUS current
     	DESCRIPTION
     	"
     		对端E1 E-3告警，1：恢复，2：告警。
       	"
        ::= { rcftE1PortTraps 19 }


   --------------------------V35端口的对象---------------------------------

    rcftV35PortTable OBJECT-TYPE
       SYNTAX  SEQUENCE OF RcftV35PortEntry
       MAX-ACCESS  not-accessible
       STATUS  current
       DESCRIPTION
       "
         The V35 PORT table.
       "
       ::= { rcftV35PortObjects 1 }

    rcftV35PortEntry OBJECT-TYPE
       SYNTAX  RcftV35PortEntry
       MAX-ACCESS  not-accessible
       STATUS  current
       DESCRIPTION
       "
          An entry in the V35 PORT table.

       "
       INDEX   { rcftChassisIndex, rcftSlotIndex,rcftV35PortIndex }
       ::= { rcftV35PortTable 1 }


    RcftV35PortEntry ::=
       SEQUENCE {
       rcftV35PortIndex		 	Integer32,
       rcftV35PortAlarmStatus	INTEGER,
       rcftV35PortStatus		INTEGER,
       rcftV35PortSpeed			Unsigned32,
       rcftV35PortBertStatus			INTEGER,
	   rcftV35PortBertTime			    Unsigned32,
	   rcftV35PortBertErrCode			Unsigned32,
	   rcftV35PortBertUnusedTime		Unsigned32,
	   rcftV35PortBertPortSpeed			Unsigned32,
	   rcftV35PortBertCodeType			INTEGER,
	   rcftV35PortBertCodeNum			INTEGER,
	   rcftV35PortLoopStatus			INTEGER,
	   rcftV35PortOrder					INTEGER
       }

    rcftV35PortIndex OBJECT-TYPE
    	SYNTAX	   Integer32
    	MAX-ACCESS read-only
    	STATUS		current
    	DESCRIPTION
    	"
    		V35口的索引
    	"
        ::= { rcftV35PortEntry 1 }

    rcftV35PortAlarmStatus	OBJECT-TYPE
    	SYNTAX	INTEGER
    	MAX-ACCESS read-only
    	STATUS		current
    	DESCRIPTION
    	"
			其它位	保留	固定000'b。
			BIT12	DSR_I		1：DSR信号UP；        0：DSR信号DOWN。

			BIT11	RAIS    站在本地设备上看对端V35口所占那一路E1的AIS告警 1：正常 	0：告警
			BIT10	RCV     站在本地设备上看对端V35口所占那一路E1的CV告警  1：正常 	0：告警
			BIT9	RLOF	站在本地设备上看对端V35口所占那一路E1的LOF告警 1：正常 	0：告警
			BIT8	AIS     V35口所占那一路E1的AIS告警 1：正常 	0：告警
			BIT7	CV      V35口所占那一路E1的CV告警  1：正常 	0：告警
			BIT6	LOF	    V35口所占那一路E1的LOF告警 1：正常 	0：告警
			BIT5	PATT		1：误码测试正常       0：误码测试告警
			BIT4    CRC_ALARM   1：正常 			  0：告警

			BIT3	DCD_O		1：DCD信号UP；        0：DCD信号DOWN。
			BIT2	CTS_O		1：CTS信号UP；        0：CTS信号DOWN。
			BIT1	DTR_I		1：DTR信号UP；        0：DTR信号DOWN。
			BIT0	RTS_I		1：RTS信号UP；        0：RTS信号DOWN。
    	"
        ::= { rcftV35PortEntry 2 }

 	rcftV35PortStatus     OBJECT-TYPE
 		SYNTAX	INTEGER
    	MAX-ACCESS read-write
    	STATUS		current
    	DESCRIPTION
    	"
    		BIT25	 V35口带宽跟随：1：跟随； 0：不跟随
    		BIT24	 V35口占用时隙的成帧模式：1：成帧； 0：透明
			BIT23-22 IN_LBK-Test 00：没有进行过内环测试； 01：保留；10：内环测试成功；11：内环测试失败。
			BIT21-20 EX_LBK-Test 00：没有进行过环回测试； 01：保留；10：外环测试成功；11：外环测试失败。
			BIT19-18 CLOCK   	 00：从时钟  01：V35终端时钟，并且V35带宽不跟随
								 10：V35终端时钟，并且V35带宽跟随  11：主时钟
			BIT17-16 LOOP_STATE  00:不环回   01：本地环回  	 10：远端环回  11：保留

			BIT15-14 Port_En  	00：端口开(DCD=0、CTS=0)；01：端口关(DCD=1、CTS=1)；10：因故障转移关；        11：保留。
			BIT13    LOC_FP_EN	1：使能本地其它端口故障向V35口转移；  0：禁止。
			BIT12    REM_FP_EN	1：使能远端V35口故障向V35口转移；0：禁止。
			BIT11    Remote CRC_EN 站在本地上看远端V35口CRC功能  1：使能      0：禁止
			BIT10	 Local CRC_EN   1：使能      0：禁止
			BIT9-8   接口方式	00：M34M；01：HDB26M；其它：保留。

			BIT7    RCLK_AN		0：RXCLK时钟固定；    1：RXCLK时钟相位适应。
			BIT6    RCLK_INV	0：RXCLK时钟正相；1：RXCLK时钟反相。
			BIT5    TCLK_INV	0：TXCLK时钟正相；1：TXCLK时钟反相。
			BIT4    SA_DISABLE	1：不使用SA bit   0：使用SA bit
			BIT3	Rate_CFG   	1：时隙带宽主控   0：时隙带宽被控
			BIT2	BERT_EN		1：误码测试使能   0：误码测试禁止
			BIT1    DATA_V		0：输入数据中断； 1：输入数据正常。
			BIT0    CLK_V		0：输入时钟异常； 1：输入时钟正常。
    	"
        ::= { rcftV35PortEntry 3 }

    rcftV35PortSpeed	OBJECT-TYPE
 		SYNTAX	Unsigned32
    	MAX-ACCESS read-write
    	STATUS		current
    	DESCRIPTION
		"
		   V35口的速率	单位为64Kbps。
		"
        ::= { rcftV35PortEntry 4 }

	rcftV35PortBertStatus		OBJECT-TYPE
	    SYNTAX  INTEGER
	    MAX-ACCESS	read-only
	    STATUS	current
	    DESCRIPTION
	    "
	    	 BIT3			BERT_STATUS		0:正常工作；	1:正在bert
	    	 BIT2-1		BERT_RESULT     00:未测试      01:测试正常；	10:测试失败
	    	 BIT0			BERT_TYPE   	0:误码率方式；  1:误码时间方式
	    "
	    ::= {rcftV35PortEntry 5 }

	rcftV35PortBertTime		OBJECT-TYPE
	    SYNTAX	Unsigned32
	    MAX-ACCESS	read-only
	    STATUS	current
	    DESCRIPTION
	    "
	    	误码率方式:测试时间，时间随测试的进行而增长,单位 S.
	    "
	    ::= {rcftV35PortEntry  6 }

	rcftV35PortBertErrCode		OBJECT-TYPE
	    SYNTAX	Unsigned32
	    MAX-ACCESS	read-only
	    STATUS	current
	    DESCRIPTION
	    "
	    	误码率方式:误码数，单位是bit
	    "
	    ::= {rcftV35PortEntry 7 }

	rcftV35PortBertUnusedTime		OBJECT-TYPE
	    SYNTAX	Unsigned32
	    MAX-ACCESS	read-only
	    STATUS	current
	    DESCRIPTION
	    "
	    	误码率方式:测试不可用时间，超过255秒后维持255秒不变，单位是S.
	    "
	    ::= {rcftV35PortEntry 8 }

	rcftV35PortBertPortSpeed		OBJECT-TYPE
	    SYNTAX	Unsigned32
	    MAX-ACCESS	read-only
	    STATUS	current
	    DESCRIPTION
	    "
	    	误码率方式:测试的端口速率，单位：kbps。
	 	"
	    ::= {rcftV35PortEntry 9 }

	rcftV35PortBertCodeType		OBJECT-TYPE
	   	SYNTAX INTEGER
	   	MAX-ACCESS	read-write
	   	STATUS	current
	   	DESCRIPTION
	   	"
	   		误码率方式:测试码型，最大值为127
	   		0000001'b：2的15次方-1；
			其它：保留。
	   	"
	   	::= {rcftV35PortEntry 10 }

	rcftV35PortBertCodeNum		OBJECT-TYPE
	   	SYNTAX INTEGER
	   	MAX-ACCESS	read-write
	   	STATUS	current
	   	DESCRIPTION
	   	"
	   		误码率方式:测试码数
	   		0010001'b：2的31次方个码；
			0010010'b：2的28次方个码；
			0010011'b：2的25次方个码；
			0010100'b：2的21次方个码；
			0100001'b：测试不停；
			其它：保留。
	   	"
	   	::= {rcftV35PortEntry 11 }

	 rcftV35PortLoopStatus	OBJECT-TYPE
	 	SYNTAX INTEGER
	    MAX-ACCESS read-only
	    STATUS current
	    DESCRIPTION
	     "
	     	E1的环回状态：1:本地环回，2：无本地环回，3：远端环回，4：无远端环回，
 			5:无环回，
 			6：本地内环使能，7：本地外环使能，8：本地双向环使能，
 			9:远端内环使能，10：远端外环使能，11：远端双向环使能，
 			12：本地内环禁止，13:本地外环禁止，14：本地双向环禁止，
 			15：远端内环禁止，16：远端外环禁止，17：远端双向环禁止，
	     "
	 	 ::= { rcftV35PortEntry 12 }

	rcftV35PortOrder	OBJECT-TYPE
		SYNTAX	INTEGER
		MAX-ACCESS	read-write
		STATUS	current
		DESCRIPTION
		"

		    1：硬复位
			2：软复位
			3：开始查询统计信息
			4：结束查询统计信息
			5：内环使能
			6：内环禁止
			7：外环使能
			8：外环禁止
			9: 无环回
			10: 本地内环使能
			11: 本地外环使能
			12: 本地双向环使能
			13: 远端内环使能
			14: 远端外环使能
			15: 远端双向环使能
			16: 本地内环禁止
			17: 本地外环禁止
			18: 本地双向环禁止
			19: 远端内环禁止
			20: 远端外环禁止
			21: 远端双向环禁止
			22: 端口BERT测试开始
			23: 端口BERT测试结束
			24：统计信息清零
			25：告警屏蔽
			26：告警屏蔽解除
			27：端口未用支路告警屏蔽
			28：端口未用支路告警屏蔽解除
			29：环回检测使能
			30：环回检测停止
			31：开始查询SFP扩展信息
			32；停止查询SFP扩展信息
			33：开始查询SFP数字诊断信息
			34：停止查询SFP数字诊断信息
			注：31-34尚没有对网管开放


			注意：对于约定5，枚举值5-9废弃，
			rcftV35PortOrder的枚举值要和其他接口级命令节点始终保持完全一致。
		"
		::= { rcftV35PortEntry 13 }
    --------------------------V35端口的告警--------------------------

       rcftV35PortDCDTrap	NOTIFICATION-TYPE
      	OBJECTS{
			rcftV35PortAlarmStatus
      	}
      	STATUS current
     	DESCRIPTION
     	"
     		局端设备上V35端口的DCD告警
     	"
     	::= { rcftV35PortTraps 1 }


       rcftV35PortCTSTrap	NOTIFICATION-TYPE
      	OBJECTS{
			rcftV35PortAlarmStatus
      	}
      	STATUS current
     	DESCRIPTION
     	"
     		局端设备上V35端口的CTS告警
     	"
     	::= { rcftV35PortTraps 2 }


       rcftV35PortDTRTrap	NOTIFICATION-TYPE
      	OBJECTS{
			rcftV35PortAlarmStatus
      	}
      	STATUS current
     	DESCRIPTION
     	"
     		局端设备上V35端口的DTR告警
     	"
     	::= { rcftV35PortTraps 3 }


       rcftV35PortRTSTrap	NOTIFICATION-TYPE
      	OBJECTS{
			rcftV35PortAlarmStatus
      	}
      	STATUS current
     	DESCRIPTION
     	"
     		局端设备上V35端口的RTS告警
     	"
     	::= { rcftV35PortTraps 4 }


       rcftV35PortCRCTrap	NOTIFICATION-TYPE
      	OBJECTS{
			rcftV35PortAlarmStatus
      	}
      	STATUS current
     	DESCRIPTION
     	"
     		局端设备上V35端口占用的那一路E1的CRC告警
     	"
     	::= { rcftV35PortTraps 5 }


       rcftV35PortPATTTrap	NOTIFICATION-TYPE
      	OBJECTS{
			rcftV35PortAlarmStatus
      	}
      	STATUS current
     	DESCRIPTION
     	"
     		局端设备上V35端口占用的那一路E1的误码测试告警
     	"
     	::= { rcftV35PortTraps 6 }


       rcftV35PortLOFTrap	NOTIFICATION-TYPE
      	OBJECTS{
			rcftV35PortAlarmStatus
      	}
      	STATUS current
     	DESCRIPTION
     	"
     		局端设备上V35端口占用的那一路E1的LOF告警
     	"
     	::= { rcftV35PortTraps 7 }


       rcftV35PortCVTrap	NOTIFICATION-TYPE
      	OBJECTS{
			rcftV35PortAlarmStatus
      	}
      	STATUS current
     	DESCRIPTION
     	"
     		局端设备上V35端口占用的那一路E1的CV告警
     	"
     	::= { rcftV35PortTraps 8 }


       rcftV35PortAISTrap	NOTIFICATION-TYPE
      	OBJECTS{
			rcftV35PortAlarmStatus
      	}
      	STATUS current
     	DESCRIPTION
     	"
     		局端设备上V35端口占用的那一路E1的AIS告警
     	"
     	::= { rcftV35PortTraps 9 }

      rcftV35PortToRLOFTrap	NOTIFICATION-TYPE
      	OBJECTS{
			rcftV35PortAlarmStatus
      	}
      	STATUS current
     	DESCRIPTION
     	"
     		站在本地设备上看对端V35口所占那一路E1的LOF告警
     	"
     	::= { rcftV35PortTraps 10 }


       rcftV35PortToRCVTrap	NOTIFICATION-TYPE
      	OBJECTS{
			rcftV35PortAlarmStatus
      	}
      	STATUS current
     	DESCRIPTION
     	"
     		站在本地设备上看对端V35口所占那一路E1的CV告警
     	"
     	::= { rcftV35PortTraps 11 }


       rcftV35PortToRAISTrap	NOTIFICATION-TYPE
      	OBJECTS{
			rcftV35PortAlarmStatus
      	}
      	STATUS current
     	DESCRIPTION
     	"
     		站在本地设备上看对端V35口所占那一路E1的AIS告警
     	"
     	::= { rcftV35PortTraps 12 }


       rcftV35PortDSRTrap	NOTIFICATION-TYPE
      	OBJECTS{
			rcftV35PortAlarmStatus
      	}
      	STATUS current
     	DESCRIPTION
     	"
     		局端设备上V35端口的DSR告警
     	"
     	::= { rcftV35PortTraps 13 }


   --------------------------G.端口的对象---------------------------------

    rcftSHDSLPortTable OBJECT-TYPE
       SYNTAX  SEQUENCE OF RcftSHDSLPortEntry
       MAX-ACCESS  not-accessible
       STATUS  current
       DESCRIPTION
       "
         The SDHSL PORT table.
       "
       ::= { rcftSHDSLPortObjects 1 }

    rcftSHDSLPortEntry OBJECT-TYPE
       SYNTAX  RcftSHDSLPortEntry
       MAX-ACCESS  not-accessible
       STATUS  current
       DESCRIPTION
       "
          An entry in the SHDSL PORT table.

       "
       INDEX   { rcftChassisIndex, rcftSlotIndex,rcftSHDSLPortIndex }
       ::= { rcftSHDSLPortTable 1 }


    RcftSHDSLPortEntry ::=
       SEQUENCE {
       rcftSHDSLPortIndex		 	Integer32,
       rcftSHDSLPortAlarmStatus		INTEGER,
       rcftSHDSLPortStatus			INTEGER,
       rcftSHDSLPortCapableSpeed	INTEGER,
       rcftSHDSLPortWorkSpeed		INTEGER,
       rcftSHDSLPortProbeMaxSpeed	INTEGER,
       rcftSHDSLPortProbeMinSpeed	INTEGER,
       rcftSDHSLPortSNR				INTEGER,
       rcftSHDSLPortConfigSNR		INTEGER,
       rcftSHDSLPortSNRThreshold   	INTEGER,
       rcftSHDSLPortAttenuation 	INTEGER,
       rcftSHDSLPortAttenuationThreshold		INTEGER,
       rcftSHDSLPortPBO   			INTEGER,
       rcftSHDSLPortLOSThreshold	INTEGER,
       rcftSHDSLPortLOSWThreshold	INTEGER,
       rcftSHDSLPortLOLKThreshold	INTEGER,
       rcftSHDSLPortESThreshold		INTEGER,
       rcftSHDSLPortLoopStatus		INTEGER,
       rcftSHDSLPortAttenuationInitThreshhold	INTEGER,
       rcftSHDSLPortBertStatus					INTEGER,
	   rcftSHDSLPortBertTime			    	Unsigned32,
	   rcftSHDSLPortBertErrCode					Unsigned32,
	   rcftSHDSLPortBertUnusedTime				Unsigned32,
	   rcftSHDSLPortBertPortSpeed				Unsigned32,
	   rcftSHDSLPortBertCodeType				INTEGER,
	   rcftSHDSLPortBertCodeNum					INTEGER,
	   rcftSHDSLPortBertCodeNum					INTEGER,
	   rcftSHDSLPortOrder						INTEGER,
	   rcftSHDSLPortOrderTimeParameter			INTEGER,
	   rcftSHDSLPortOrderModeParameter			INTEGER
       }

    rcftSHDSLPortIndex OBJECT-TYPE
    	SYNTAX	   Integer32
    	MAX-ACCESS read-only
    	STATUS		current
    	DESCRIPTION
    	"
    		G.口的索引
    	"
        ::= { rcftSHDSLPortEntry 1 }

     rcftSHDSLPortAlarmStatus   OBJECT-TYPE
     	SYNTAX	INTEGER
     	MAX-ACCESS	read-only
     	STATUS		current
     	DESCRIPTION
     	"
     		G.口的告警状态。

     		BIT5: SHDSL-LOS	SHDSL端口LOS时该位清0，否则置1。
            BIT4: SHDSL-LOSW	SHDSL端口LOSW时该位清0，否则置1。
            BIT3: SHDSL-Link	SHDSL端口为link up状态该位置1，否则清0。
            BIT2: 保留	固定为0'b。
            BIT1: FEC	SHDSL端口有FEC错误时该位清0，否则置1。
            BIT0: CRC	SHDSL端口有CRC错误时该位清0，否则置1。
     	"
 	    ::= { rcftSHDSLPortEntry 2 }


      rcftSHDSLPortStatus   OBJECT-TYPE
     	SYNTAX	INTEGER
     	MAX-ACCESS	read-write
     	STATUS		current
     	DESCRIPTION
     	"
     		G.口的状态。
			BIT23-22 IN_LBK-Test 00：没有进行过环回测试； 01：保留；10：内环测试成功；11：内环测试失败。
			BIT21-20 EX_LBK-Test 00：没有进行过环回测试； 01：保留；10：外环测试成功；11：外环测试失败。
            BIT19-16 保留
     		BIT15-14 Port_En 	00：端口开；01：端口关；10：因故障转移关（无）；11：保留。
     		BIT13    LOC_FP_EN	1：使能本地xx端口故障向SHDSL口转移；  0：禁止。
			BIT12    REM_FP_EN	1：使能远端xx端口故障向SHDSL口转移；  0：禁止。
			BIT11	 BOOT状态	0：BOOT失败；1：BOOT成功。
			BIT10-9 保留
			BIT8	SHDSL-synClock:   0:同步时钟， 1：准同步时钟
			BIT7-6	编码方式	00'b：TC-4PAM； 01'b：TC-16PAM；10'b：TC-32PAM。11'b：保留。
			BIT5-4	SHDSL-Annex	SHDSL端口采用AnnexA时：01b；为AnnexB时：10b；为AnnexF时：11b。
			BIT3	SHDSL-PSD	SHDSL端口采用对称PSD时该位置1，非对称PSD时清0。
			BIT2	SHDSL-Port-En	SHDSL端口为打开状态该位置1，为关闭状态则清0。
			BIT1	SHDSL-LineProbe	SHDSL端口为线路探测使能方式该位置1；否则清0。网管不需要处理！
			BIT0	STU-C	SHDSL端口工作于STU-C模式时该位置1，否则清0。
     	"
 	    ::= { rcftSHDSLPortEntry 3 }

	  rcftSHDSLPortCapableSpeed	OBJECT-TYPE
	  	SYNTAX	INTEGER
     	MAX-ACCESS	read-only
     	STATUS		current
     	DESCRIPTION
     	"
     		G.口最大可用速率,单位为64Kbps。
	  	"
	    ::= { rcftSHDSLPortEntry 4 }


	  rcftSHDSLPortWorkSpeed OBJECT-TYPE
     	SYNTAX	INTEGER
     	MAX-ACCESS	read-only
     	STATUS		current
     	DESCRIPTION
     	"
     		G.口的工作速率,单位为64Kbps。
     	"
 	    ::= { rcftSHDSLPortEntry 5 }

	  rcftSHDSLPortProbeMaxSpeed OBJECT-TYPE
     	SYNTAX	INTEGER
     	MAX-ACCESS	read-write
     	STATUS		current
     	DESCRIPTION
     	"
     		G.口处于线路探测方式时配置的允许最高速率,单位为64Kbps。
     	"
 	    ::= { rcftSHDSLPortEntry 6 }

	  rcftSHDSLPortProbeMinSpeed OBJECT-TYPE
     	SYNTAX	INTEGER
     	MAX-ACCESS	read-write
     	STATUS		current
     	DESCRIPTION
     	"
     		G.口处于线路探测方式时配置的允许最低速率,单位为64Kbps。
     	"
 	    ::= { rcftSHDSLPortEntry 7 }


 		rcftSDHSLPortSNR    OBJECT-TYPE
	     	SYNTAX	INTEGER
	     	MAX-ACCESS	read-only
	     	STATUS		current
	     	DESCRIPTION
	     	"
	     		G.口正常工作时的SNR（信噪比）,单位为0.5dB。是有符号数，有可能是负数。
	     	"
	 	    ::= { rcftSHDSLPortEntry 8 }

 		rcftSHDSLPortConfigSNR    OBJECT-TYPE
	     	SYNTAX	INTEGER
	     	MAX-ACCESS	read-write
	     	STATUS		current
	     	DESCRIPTION
	     	"
	     		G.口初始设置的SNR（信噪比）,单位为0.5dB。当linkup的瞬间G.口工作的SNR必须大于该
	     		初始值，之后rcftSDHSLPortSNR可以小于该初始值。是有符号数，有可能是负数。
	     	"
	 	    ::= { rcftSHDSLPortEntry 9 }

 	    rcftSHDSLPortSNRThreshold	OBJECT-TYPE
	     	SYNTAX	INTEGER
	     	MAX-ACCESS	read-write
	     	STATUS		current
	     	DESCRIPTION
	     	"
	     		G.口SNR（信噪比）的门限值,单位为0.5dB。
	     		当rcftSDHSLPortSNR小于该值时,AGENT发送告警。是有符号数，有可能是负数。
	     	"
	 	    ::= { rcftSHDSLPortEntry 10 }



 	    rcftSHDSLPortAttenuation	OBJECT-TYPE
	     	SYNTAX	INTEGER
	     	MAX-ACCESS	read-only
	     	STATUS		current
	     	DESCRIPTION
	     	"
	     		G.口的线路衰减值,单位为0.5dB。
	     	"
	 	    ::= { rcftSHDSLPortEntry 11 }


 	    rcftSHDSLPortAttenuationThreshold	OBJECT-TYPE
	     	SYNTAX	INTEGER
	     	MAX-ACCESS	read-write
	     	STATUS		current
	     	DESCRIPTION
	     	"
	     		G.口线路衰减值的门限值,单位为0.5dB。当rcftSHDSLPortAttenuation大于该门限值时
	     		AGENT发送告警。
	     	"
	 	    ::= { rcftSHDSLPortEntry 12 }

 	   	rcftSHDSLPortPBO  OBJECT-TYPE
	     	SYNTAX	INTEGER
	     	MAX-ACCESS	read-write
	     	STATUS		current
	     	DESCRIPTION
	     	"
	     		G.口线路功率回退结果
				BIT7	Valid	结果值有意义时为1，否则清0（0-6位无意义）。
				BIT6	PBO_AUTO	PBO自动设置时该位置1，PBO固定设置则清0。
				BIT5-4	保留	固定为00'b。
				BIT3-0	PBO值	PBO实际值，单位为dB。

	     	"
	 	    ::= { rcftSHDSLPortEntry 13 }

	 	 rcftSHDSLPortLOSThreshold OBJECT-TYPE
	     	SYNTAX	INTEGER
	     	MAX-ACCESS	read-write
	     	STATUS		current
	     	DESCRIPTION
	     	"
	     		当前15分钟LOS次数告警门限。取值范围是0-255。
	     	"
	 	    ::= { rcftSHDSLPortEntry 14 }


	 	 rcftSHDSLPortLOSWThreshold OBJECT-TYPE
	     	SYNTAX	INTEGER
	     	MAX-ACCESS	read-write
	     	STATUS		current
	     	DESCRIPTION
	     	"
	     		当前15分钟LOSW次数告警门限。取值范围是0-255。
	     	"
	 	    ::= { rcftSHDSLPortEntry 15 }


	 	 rcftSHDSLPortLOLKThreshold OBJECT-TYPE
	     	SYNTAX	INTEGER
	     	MAX-ACCESS	read-write
	     	STATUS		current
	     	DESCRIPTION
	     	"
	     		当前15分钟LOLK(linkdown)次数告警门限。取值范围是0-255。
	     	"
	 	    ::= { rcftSHDSLPortEntry 16 }

	 	 rcftSHDSLPortESThreshold OBJECT-TYPE
	     	SYNTAX	INTEGER
	     	MAX-ACCESS	read-write
	     	STATUS		current
	     	DESCRIPTION
	     	"
	     		当前15分钟误码秒告警门限。取值范围是0-255。
	     	"
	 	    ::= { rcftSHDSLPortEntry 17 }


	 	  rcftSHDSLPortLoopStatus	OBJECT-TYPE
	 	  	SYNTAX	INTEGER
	 	  	{
	 	  		insideLoop(1),
	 	  		outsideLoop(2),
	 	  		doubleloop(3),
	 	  		normal(100)
	 	  	}
	     	MAX-ACCESS	read-only
	     	STATUS		current
	     	DESCRIPTION
	     	"
	     		G.口的环回状态:1：内环，2：外环，3：内环外环同时存在,100：正常
	     		对于约定四，统一为以下枚举值：
	     		E1的环回状态：1:本地环回，2：无本地环回，3：远端环回，4：无远端环回，
 				5:无环回，
 				6：本地内环使能，7：本地外环使能，8：本地双向环使能，
 				9:远端内环使能，10：远端外环使能，11：远端双向环使能，
 				12：本地内环禁止，13:本地外环禁止，14：本地双向环禁止，
 				15：远端内环禁止，16：远端外环禁止，17：远端双向环禁止，
	     	"
	 	    ::= { rcftSHDSLPortEntry 18 }

 	    rcftSHDSLPortAttenuationInitThreshhold	OBJECT-TYPE
	     	SYNTAX	INTEGER
	     	MAX-ACCESS	read-write
	     	STATUS		current
	     	DESCRIPTION
	     	"
	     		G.口的环路衰减初始门限值，单位为0.5dB。
	     	"
	 	    ::= { rcftSHDSLPortEntry 19 }

	    rcftSHDSLPortBertStatus		OBJECT-TYPE
	    	SYNTAX  INTEGER
	    	MAX-ACCESS	read-only
	    	STATUS	current
	    	DESCRIPTION
	    	"
	    	  BIT3			BERT_STATUS		0:正常工作；	1:正在bert
	    	  BIT2-1		BERT_RESULT     00:未测试      01:测试正常；	10:测试失败
	    	  BIT0			BERT_TYPE   	0:误码率方式；  1:误码时间方式
	    	"
	    	::= {rcftSHDSLPortEntry 20}

	    rcftSHDSLPortBertTime		OBJECT-TYPE
	    	SYNTAX	Unsigned32
	    	MAX-ACCESS	read-only
	    	STATUS	current
	    	DESCRIPTION
	    	"
	    	误码率方式:测试时间，时间随测试的进行而增长,单位 S.
	    	"
	    	::= {rcftSHDSLPortEntry  21}

	    rcftSHDSLPortBertErrCode		OBJECT-TYPE
	    	SYNTAX	Unsigned32
	    	MAX-ACCESS	read-only
	    	STATUS	current
	    	DESCRIPTION
	    	"
	    	 误码率方式:误码数，单位是bit
	    	"
	    	::= {rcftSHDSLPortEntry 22}

	    rcftSHDSLPortBertUnusedTime		OBJECT-TYPE
	    	SYNTAX	Unsigned32
	    	MAX-ACCESS	read-only
	    	STATUS	current
	    	DESCRIPTION
	    	"
	    	 误码率方式:测试不可用时间，超过255秒后维持255秒不变，单位是S.
	    	"
	    	::= {rcftSHDSLPortEntry 23}

	    rcftSHDSLPortBertPortSpeed		OBJECT-TYPE
	    	SYNTAX	Unsigned32
	    	MAX-ACCESS	read-only
	    	STATUS	current
	    	DESCRIPTION
	    	"
	    	 误码率方式:测试的端口速率，单位：kbps。
	    	"
	    	::= {rcftSHDSLPortEntry 24}

	    rcftSHDSLPortBertCodeType		OBJECT-TYPE
	   		SYNTAX INTEGER
	   		MAX-ACCESS	read-write
	   		STATUS	current
	   		DESCRIPTION
	   		"
	   		误码率方式:测试码型，最大值为127
	   		0000001'b：2的15次方-1；
			其它：保留。

	   		"
	   		::= {rcftSHDSLPortEntry 25}

	    rcftSHDSLPortBertCodeNum		OBJECT-TYPE
	   		SYNTAX INTEGER
	   		MAX-ACCESS	read-write
	   		STATUS	current
	   		DESCRIPTION
	   		"
	   		误码率方式:测试码数
	   		0000001'b：2的31次方个码；
			0000010'b：2的28次方个码；
			0000011'b：2的25次方个码；
			0000100'b：2的21次方个码；
			1111111'b：测试不停；
			其它：保留。

	   		"
	   		::= {rcftSHDSLPortEntry 26}

		rcftSHDSLPortOrder	OBJECT-TYPE
			SYNTAX	INTEGER
			MAX-ACCESS	read-write
			STATUS	current
			DESCRIPTION
			"
			    1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
				22: 端口BERT测试开始
				23: 端口BERT测试结束
				24：统计信息清零
				25：告警屏蔽
				26：告警屏蔽解除
				27：端口未用支路告警屏蔽
				28：端口未用支路告警屏蔽解除
				29：环回检测使能
				30：环回检测停止
				31：开始查询SFP扩展信息
				32；停止查询SFP扩展信息
				33：开始查询SFP数字诊断信息
				34：停止查询SFP数字诊断信息
				注：31-34尚没有对网管开放


			注意：对于约定5，枚举值5-9废弃，
			rcftSHDSLPortOrder的枚举值要和其他接口级命令节点始终保持完全一致。

			"
		::= { rcftSHDSLPortEntry 27 }

		rcftSHDSLPortOrderTimeParameter	OBJECT-TYPE
			SYNTAX	INTEGER
			MAX-ACCESS	read-write
			STATUS	current
			DESCRIPTION
			"
	  		    给局端模块G.口发送命令时所需要赋的时长参数。

	  		    1: 测试时长1分钟
	  		    2: 测试时长2分钟
	  		    3: 测试时长4分钟
	  		    4: 测试时长8分钟
	  		    5: 测试时长15分钟
	  		    6: 测试时长30分钟
	  		    7: 测试时长60分钟

	  		    18: 测试2帧
	  		    19: 测试5帧
	  		    20: 测试10帧
	  		    21: 测试20帧
	  		    22: 测试50帧
	  		    23: 测试100帧

	  		    32: 测试终止
	  		    33：测试时间/帧数不限
			"
		::= { rcftSHDSLPortEntry 28 }

		rcftSHDSLPortOrderModeParameter	OBJECT-TYPE
			SYNTAX	INTEGER
			MAX-ACCESS	read-write
			STATUS	current
			DESCRIPTION
			"
	  		    给局端模块G.口发送命令时所需要赋的模式参数。

		    	  BIT5		MAC_ADDR_EXCH	0:正常环回；	1:交换 MAC 地址
		    	  BIT4		CRC_RECAL		0:正常环回；	1:重新计算CRC
		    	  BIT3		DATA_OUT		0:不输出；	1:环回数据同时在另一侧输出
		    	  BIT2		DATA_GENERATE   0:环回输入数据  1:产生测试数据；
		    	  BIT1		UTILITY	        0:速率为10%     1:速率为100%
		    	  BIT0		FRAME_LENGTH   	0:帧长62字节；  1:帧长1518字节

				  注意：BIT0和BIT1只有在BIT2为1的时候有效。
			"
		::= { rcftSHDSLPortEntry 29 }

	 	 rcftSHDSLPortCurrentTable OBJECT-TYPE
	 	 	SYNTAX  SEQUENCE OF RcftSHDSLPortCurrentEntry
	 	 	MAX-ACCESS not-accessible
	 	 	STATUS current
	 	 	DESCRIPTION
	 	 	"
	 	 		G.口当前15分钟的性能统计表
	 	 	"
	 		::= { rcftSHDSLPortPerformance 1 }


	 	 rcftSHDSLPortCurrentEntry OBJECT-TYPE
 	      	SYNTAX  RcftSHDSLPortCurrentEntry
	 	 	MAX-ACCESS not-accessible
	 	 	STATUS current
	 	 	DESCRIPTION
	 	 	"
	 	 		G.口当前15分钟的性能统计表
	 	 	"
 	 	    INDEX{ rcftChassisIndex, rcftSlotIndex,rcftSHDSLPortIndex }
	 		::= { rcftSHDSLPortCurrentTable 1 }


	 	 RcftSHDSLPortCurrentEntry ::=
	 	 	SEQUENCE{
	 	 	rcftSHDSLPortCurrentLOSTimes 	INTEGER,
	 	 	rcftSHDSLPortCurrentLOSWTimes 	INTEGER,
	 	 	rcftSHDSLPortCurrentLOLKTimes 	INTEGER,
	 	 	rcftSHDSLPortCurrentCVTimes 	INTEGER,
	 	 	rcftSHDSLPortCurrentES			INTEGER,
	 	 	rcftSHDSLPortCurrentSES			INTEGER,
	 	 	rcftSHDSLPortCurrentUAS			INTEGER,
	 	 	rcftSHDSLPortCurrentLOSWS      	INTEGER,
	 	 	rcftSHDSLPortCurrentLOFTimes 	INTEGER,
	 	 	rcftSHDSLPortCurrentCRCTimes 	INTEGER
	 	 }

	 	rcftSHDSLPortCurrentLOSTimes OBJECT-TYPE
	     	SYNTAX	INTEGER
	     	MAX-ACCESS	read-only
	     	STATUS		current
	     	DESCRIPTION
	     	"
	     		G.口当前15分钟的LOS次数
	     	"
            ::= { rcftSHDSLPortCurrentEntry 1 }


	 	rcftSHDSLPortCurrentLOSWTimes OBJECT-TYPE
	     	SYNTAX	INTEGER
	     	MAX-ACCESS	read-only
	     	STATUS		current
	     	DESCRIPTION
	     	"
	     		G.口当前15分钟的LOSW次数
	     	"
            ::= { rcftSHDSLPortCurrentEntry 2 }


	 	rcftSHDSLPortCurrentLOLKTimes OBJECT-TYPE
	     	SYNTAX	INTEGER
	     	MAX-ACCESS	read-only
	     	STATUS		current
	     	DESCRIPTION
	     	"
	     		G.口当前15分钟的LINK DOWN的次数
	     	"
            ::= { rcftSHDSLPortCurrentEntry 3 }

	 	rcftSHDSLPortCurrentCVTimes OBJECT-TYPE
	     	SYNTAX	INTEGER
	     	MAX-ACCESS	read-only
	     	STATUS		current
	     	DESCRIPTION
	     	"
	     		G.口当前15分钟的CV的次数
	     	"
            ::= { rcftSHDSLPortCurrentEntry 4 }


	 	rcftSHDSLPortCurrentES OBJECT-TYPE
	     	SYNTAX	INTEGER
	     	MAX-ACCESS	read-only
	     	STATUS		current
	     	DESCRIPTION
	     	"
	     		G.口当前15分钟的误码秒数
	     	"
            ::= { rcftSHDSLPortCurrentEntry 5 }

	 	rcftSHDSLPortCurrentSES OBJECT-TYPE
	     	SYNTAX	INTEGER
	     	MAX-ACCESS	read-only
	     	STATUS		current
	     	DESCRIPTION
	     	"
	     		G.口当前15分钟的严重误码秒数
	     	"
            ::= { rcftSHDSLPortCurrentEntry 6 }

	 	rcftSHDSLPortCurrentUAS OBJECT-TYPE
	     	SYNTAX	INTEGER
	     	MAX-ACCESS	read-only
	     	STATUS		current
	     	DESCRIPTION
	     	"
	     		G.口当前15分钟的不可用秒数
	     	"
            ::= { rcftSHDSLPortCurrentEntry 7 }

	 	rcftSHDSLPortCurrentLOSWS OBJECT-TYPE
	     	SYNTAX	INTEGER
	     	MAX-ACCESS	read-only
	     	STATUS		current
	     	DESCRIPTION
	     	"
	     		G.口当前15分钟的LOSW秒数
	     	"
            ::= { rcftSHDSLPortCurrentEntry 8 }

	 	rcftSHDSLPortCurrentLOFTimes OBJECT-TYPE
	     	SYNTAX	INTEGER
	     	MAX-ACCESS	read-only
	     	STATUS		current
	     	DESCRIPTION
	     	"
	     		G.口当前15分钟的LOF的次数
	     	"
            ::= { rcftSHDSLPortCurrentEntry 9 }

	 	rcftSHDSLPortCurrentCRCTimes OBJECT-TYPE
	     	SYNTAX	INTEGER
	     	MAX-ACCESS	read-only
	     	STATUS		current
	     	DESCRIPTION
	     	"
	     		G.口当前15分钟的CRC的次数
	     	"
            ::= { rcftSHDSLPortCurrentEntry 10 }

	 	 rcftSHDSLPortIntervalTable OBJECT-TYPE
	 	 	SYNTAX  SEQUENCE OF RcftSHDSLPortIntervalEntry
	 	 	MAX-ACCESS not-accessible
	 	 	STATUS current
	 	 	DESCRIPTION
	 	 	"
	 	 		G.口最近若干个15分钟的性能统计表
	 	 	"
	 		::= { rcftSHDSLPortPerformance 2 }


	 	 rcftSHDSLPortIntervalEntry OBJECT-TYPE
 	      	SYNTAX  RcftSHDSLPortIntervalEntry
	 	 	MAX-ACCESS not-accessible
	 	 	STATUS current
	 	 	DESCRIPTION
	 	 	"
	 	 		G.口最近若干个15分钟的性能统计表
	 	 	"
 	 	    INDEX{ rcftChassisIndex, rcftSlotIndex,rcftSHDSLPortIndex,rcftSHDSLPortIntervalNumber }
	 		::= { rcftSHDSLPortIntervalTable 1 }


	 	 RcftSHDSLPortIntervalEntry ::=
	 	 	SEQUENCE{
	 	 	rcftSHDSLPortIntervalNumber		INTEGER,
	 	 	rcftSHDSLPortIntervalLOSTimes 	INTEGER,
	 	 	rcftSHDSLPortIntervalLOSWTimes 	INTEGER,
	 	 	rcftSHDSLPortIntervalLOLKTimes 	INTEGER,
	 	 	rcftSHDSLPortIntervalCVTimes 	INTEGER,
	 	 	rcftSHDSLPortIntervalES			INTEGER,
	 	 	rcftSHDSLPortIntervalSES		INTEGER,
	 	 	rcftSHDSLPortIntervalUAS		INTEGER,
	 	 	rcftSHDSLPortIntervalLOSWS      INTEGER,
	 	 	rcftSHDSLPortIntervalLOFTimes 	INTEGER,
	 	 	rcftSHDSLPortIntervalCRCTimes 	INTEGER
	 	 }

	 	rcftSHDSLPortIntervalNumber  OBJECT-TYPE
	     	SYNTAX	INTEGER
	     	MAX-ACCESS	read-only
	     	STATUS		current
	     	DESCRIPTION
	     	"
	     		G.口最近的第几个15分钟
	     	"
            ::= { rcftSHDSLPortIntervalEntry 1 }


	 	rcftSHDSLPortIntervalLOSTimes OBJECT-TYPE
	     	SYNTAX	INTEGER
	     	MAX-ACCESS	read-only
	     	STATUS		current
	     	DESCRIPTION
	     	"
	     		G.口最近第几个15分钟的LOS次数
	     	"
            ::= { rcftSHDSLPortIntervalEntry 2 }


	 	rcftSHDSLPortIntervalLOSWTimes OBJECT-TYPE
	     	SYNTAX	INTEGER
	     	MAX-ACCESS	read-only
	     	STATUS		current
	     	DESCRIPTION
	     	"
	     		G.口最近第几个15分钟的LOSW次数
	     	"
            ::= { rcftSHDSLPortIntervalEntry 3 }


	 	rcftSHDSLPortIntervalLOLKTimes OBJECT-TYPE
	     	SYNTAX	INTEGER
	     	MAX-ACCESS	read-only
	     	STATUS		current
	     	DESCRIPTION
	     	"
	     		G.口最近第几个15分钟的LINK DOWN的次数
	     	"
            ::= { rcftSHDSLPortIntervalEntry 4 }

	 	rcftSHDSLPortIntervalCVTimes OBJECT-TYPE
	     	SYNTAX	INTEGER
	     	MAX-ACCESS	read-only
	     	STATUS		current
	     	DESCRIPTION
	     	"
	     		G.口最近第几个15分钟的CV的次数
	     	"
            ::= { rcftSHDSLPortIntervalEntry 5 }


	 	rcftSHDSLPortIntervalES OBJECT-TYPE
	     	SYNTAX	INTEGER
	     	MAX-ACCESS	read-only
	     	STATUS		current
	     	DESCRIPTION
	     	"
	     		G.口最近第几个15分钟的误码秒数
	     	"
            ::= { rcftSHDSLPortIntervalEntry 6 }

	 	rcftSHDSLPortIntervalSES OBJECT-TYPE
	     	SYNTAX	INTEGER
	     	MAX-ACCESS	read-only
	     	STATUS		current
	     	DESCRIPTION
	     	"
	     		G.口最近第几个15分钟的严重误码秒数
	     	"
            ::= { rcftSHDSLPortIntervalEntry 7 }

	 	rcftSHDSLPortIntervalUAS OBJECT-TYPE
	     	SYNTAX	INTEGER
	     	MAX-ACCESS	read-only
	     	STATUS		current
	     	DESCRIPTION
	     	"
	     		G.口最近第几个15分钟的不可用秒数
	     	"
            ::= { rcftSHDSLPortIntervalEntry 8 }

	 	rcftSHDSLPortIntervalLOSWS OBJECT-TYPE
	     	SYNTAX	INTEGER
	     	MAX-ACCESS	read-only
	     	STATUS		current
	     	DESCRIPTION
	     	"
	     		G.口最近第几个15分钟的LOSW秒数
	     	"
            ::= { rcftSHDSLPortIntervalEntry 9 }

	 	rcftSHDSLPortIntervalLOFTimes OBJECT-TYPE
	     	SYNTAX	INTEGER
	     	MAX-ACCESS	read-only
	     	STATUS		current
	     	DESCRIPTION
	     	"
	     		G.口最近第几个15分钟的LOF次数
	     	"
            ::= { rcftSHDSLPortIntervalEntry 10 }

	 	rcftSHDSLPortIntervalCRCTimes OBJECT-TYPE
	     	SYNTAX	INTEGER
	     	MAX-ACCESS	read-only
	     	STATUS		current
	     	DESCRIPTION
	     	"
	     		G.口最近第几个15分钟的CRC次数
	     	"
            ::= { rcftSHDSLPortIntervalEntry 11 }


	 	 rcftSHDSLPortCurrentDayTable OBJECT-TYPE
	 	 	SYNTAX  SEQUENCE OF RcftSHDSLPortCurrentDayEntry
	 	 	MAX-ACCESS not-accessible
	 	 	STATUS current
	 	 	DESCRIPTION
	 	 	"
	 	 		G.口当前24小时的性能统计表
	 	 	"
	 		::= { rcftSHDSLPortPerformance 3 }


	 	 rcftSHDSLPortCurrentDayEntry OBJECT-TYPE
 	      	SYNTAX  RcftSHDSLPortCurrentDayEntry
	 	 	MAX-ACCESS not-accessible
	 	 	STATUS current
	 	 	DESCRIPTION
	 	 	"
	 	 		G.口当前24小时的性能统计表
	 	 	"
 	 	    INDEX{ rcftChassisIndex, rcftSlotIndex,rcftSHDSLPortIndex }
	 		::= { rcftSHDSLPortCurrentDayTable 1 }


	 	 RcftSHDSLPortCurrentDayEntry ::=
	 	 	SEQUENCE{
	 	 	rcftSHDSLPortCurrentDayLOSTimes 	INTEGER,
	 	 	rcftSHDSLPortCurrentDayLOSWTimes 	INTEGER,
	 	 	rcftSHDSLPortCurrentDayLOLKTimes 	INTEGER,
	 	 	rcftSHDSLPortCurrentDayCVTimes 	INTEGER,
	 	 	rcftSHDSLPortCurrentDayES			INTEGER,
	 	 	rcftSHDSLPortCurrentDaySES		INTEGER,
	 	 	rcftSHDSLPortCurrentDayUAS		INTEGER,
	 	 	rcftSHDSLPortCurrentDayLOSWS      INTEGER,
	 	 	rcftSHDSLPortCurrentDayLOFTimes 	INTEGER,
	 	 	rcftSHDSLPortCurrentDayCRCTimes 	INTEGER
	 	 }

	 	rcftSHDSLPortCurrentDayLOSTimes OBJECT-TYPE
	     	SYNTAX	INTEGER
	     	MAX-ACCESS	read-only
	     	STATUS		current
	     	DESCRIPTION
	     	"
	     		G.口当前24小时的LOS次数
	     	"
            ::= { rcftSHDSLPortCurrentDayEntry 1 }


	 	rcftSHDSLPortCurrentDayLOSWTimes OBJECT-TYPE
	     	SYNTAX	INTEGER
	     	MAX-ACCESS	read-only
	     	STATUS		current
	     	DESCRIPTION
	     	"
	     		G.口当前24小时的LOSW次数
	     	"
            ::= { rcftSHDSLPortCurrentDayEntry 2 }


	 	rcftSHDSLPortCurrentDayLOLKTimes OBJECT-TYPE
	     	SYNTAX	INTEGER
	     	MAX-ACCESS	read-only
	     	STATUS		current
	     	DESCRIPTION
	     	"
	     		G.口当前24小时的LINK DOWN的次数
	     	"
            ::= { rcftSHDSLPortCurrentDayEntry 3 }

	 	rcftSHDSLPortCurrentDayCVTimes OBJECT-TYPE
	     	SYNTAX	INTEGER
	     	MAX-ACCESS	read-only
	     	STATUS		current
	     	DESCRIPTION
	     	"
	     		G.口当前24小时的CV的次数
	     	"
            ::= { rcftSHDSLPortCurrentDayEntry 4 }


	 	rcftSHDSLPortCurrentDayES OBJECT-TYPE
	     	SYNTAX	INTEGER
	     	MAX-ACCESS	read-only
	     	STATUS		current
	     	DESCRIPTION
	     	"
	     		G.口当前24小时的误码秒数
	     	"
            ::= { rcftSHDSLPortCurrentDayEntry 5 }

	 	rcftSHDSLPortCurrentDaySES OBJECT-TYPE
	     	SYNTAX	INTEGER
	     	MAX-ACCESS	read-only
	     	STATUS		current
	     	DESCRIPTION
	     	"
	     		G.口当前24小时的严重误码秒数
	     	"
            ::= { rcftSHDSLPortCurrentDayEntry 6 }

	 	rcftSHDSLPortCurrentDayUAS OBJECT-TYPE
	     	SYNTAX	INTEGER
	     	MAX-ACCESS	read-only
	     	STATUS		current
	     	DESCRIPTION
	     	"
	     		G.口当前24小时的不可用秒数
	     	"
            ::= { rcftSHDSLPortCurrentDayEntry 7 }

	 	rcftSHDSLPortCurrentDayLOSWS OBJECT-TYPE
	     	SYNTAX	INTEGER
	     	MAX-ACCESS	read-only
	     	STATUS		current
	     	DESCRIPTION
	     	"
	     		G.口当前24小时的LOSW秒数
	     	"
            ::= { rcftSHDSLPortCurrentDayEntry 8 }

	 	rcftSHDSLPortCurrentDayLOFTimes OBJECT-TYPE
	     	SYNTAX	INTEGER
	     	MAX-ACCESS	read-only
	     	STATUS		current
	     	DESCRIPTION
	     	"
	     		G.口当前24小时的LOF次数
	     	"
            ::= { rcftSHDSLPortCurrentDayEntry 9 }

	 	rcftSHDSLPortCurrentDayCRCTimes OBJECT-TYPE
	     	SYNTAX	INTEGER
	     	MAX-ACCESS	read-only
	     	STATUS		current
	     	DESCRIPTION
	     	"
	     		G.口当前24小时的CRC次数
	     	"
            ::= { rcftSHDSLPortCurrentDayEntry 10 }


	 	 rcftSHDSLPortIntervalDayTable OBJECT-TYPE
	 	 	SYNTAX  SEQUENCE OF RcftSHDSLPortIntervalDayEntry
	 	 	MAX-ACCESS not-accessible
	 	 	STATUS current
	 	 	DESCRIPTION
	 	 	"
	 	 		G.口最近若干个24小时的性能统计表
	 	 	"
	 		::= { rcftSHDSLPortPerformance 4 }


	 	 rcftSHDSLPortIntervalDayEntry OBJECT-TYPE
 	      	SYNTAX  RcftSHDSLPortIntervalDayEntry
	 	 	MAX-ACCESS not-accessible
	 	 	STATUS current
	 	 	DESCRIPTION
	 	 	"
	 	 		G.口最近若干个24小时的性能统计表
	 	 	"
 	 	    INDEX{ rcftChassisIndex, rcftSlotIndex,rcftSHDSLPortIndex,rcftSHDSLPortIntervalDayNumber }
	 		::= { rcftSHDSLPortIntervalDayTable 1 }


	 	 RcftSHDSLPortIntervalDayEntry ::=
	 	 	SEQUENCE{
	 	 	rcftSHDSLPortIntervalDayNumber		INTEGER,
	 	 	rcftSHDSLPortIntervalDayLOSTimes 	INTEGER,
	 	 	rcftSHDSLPortIntervalDayLOSWTimes 	INTEGER,
	 	 	rcftSHDSLPortIntervalDayLOLKTimes 	INTEGER,
	 	 	rcftSHDSLPortIntervalDayCVTimes 	INTEGER,
	 	 	rcftSHDSLPortIntervalDayES			INTEGER,
	 	 	rcftSHDSLPortIntervalDaySES		INTEGER,
	 	 	rcftSHDSLPortIntervalDayUAS		INTEGER,
	 	 	rcftSHDSLPortIntervalDayLOSWS      INTEGER,
	 	 	rcftSHDSLPortIntervalDayLOFTimes 	INTEGER,
	 	 	rcftSHDSLPortIntervalDayCRCTimes 	INTEGER
	 	 }

	 	rcftSHDSLPortIntervalDayNumber  OBJECT-TYPE
	     	SYNTAX	INTEGER
	     	MAX-ACCESS	read-only
	     	STATUS		current
	     	DESCRIPTION
	     	"
	     		G.口最近的第几个24小时
	     	"
            ::= { rcftSHDSLPortIntervalDayEntry 1 }


	 	rcftSHDSLPortIntervalDayLOSTimes OBJECT-TYPE
	     	SYNTAX	INTEGER
	     	MAX-ACCESS	read-only
	     	STATUS		current
	     	DESCRIPTION
	     	"
	     		G.口最近第几个24小时的LOS次数
	     	"
            ::= { rcftSHDSLPortIntervalDayEntry 2 }


	 	rcftSHDSLPortIntervalDayLOSWTimes OBJECT-TYPE
	     	SYNTAX	INTEGER
	     	MAX-ACCESS	read-only
	     	STATUS		current
	     	DESCRIPTION
	     	"
	     		G.口最近第几个24小时的LOSW次数
	     	"
            ::= { rcftSHDSLPortIntervalDayEntry 3 }


	 	rcftSHDSLPortIntervalDayLOLKTimes OBJECT-TYPE
	     	SYNTAX	INTEGER
	     	MAX-ACCESS	read-only
	     	STATUS		current
	     	DESCRIPTION
	     	"
	     		G.口最近第几个24小时的LINK DOWN的次数
	     	"
            ::= { rcftSHDSLPortIntervalDayEntry 4 }

	 	rcftSHDSLPortIntervalDayCVTimes OBJECT-TYPE
	     	SYNTAX	INTEGER
	     	MAX-ACCESS	read-only
	     	STATUS		current
	     	DESCRIPTION
	     	"
	     		G.口最近第几个24小时的CV的次数
	     	"
            ::= { rcftSHDSLPortIntervalDayEntry 5 }


	 	rcftSHDSLPortIntervalDayES OBJECT-TYPE
	     	SYNTAX	INTEGER
	     	MAX-ACCESS	read-only
	     	STATUS		current
	     	DESCRIPTION
	     	"
	     		G.口最近第几个24小时的误码秒数
	     	"
            ::= { rcftSHDSLPortIntervalDayEntry 6 }

	 	rcftSHDSLPortIntervalDaySES OBJECT-TYPE
	     	SYNTAX	INTEGER
	     	MAX-ACCESS	read-only
	     	STATUS		current
	     	DESCRIPTION
	     	"
	     		G.口最近第几个24小时的严重误码秒数
	     	"
            ::= { rcftSHDSLPortIntervalDayEntry 7 }

	 	rcftSHDSLPortIntervalDayUAS OBJECT-TYPE
	     	SYNTAX	INTEGER
	     	MAX-ACCESS	read-only
	     	STATUS		current
	     	DESCRIPTION
	     	"
	     		G.口最近第几个24小时的不可用秒数
	     	"
            ::= { rcftSHDSLPortIntervalDayEntry 8 }

	 	rcftSHDSLPortIntervalDayLOSWS OBJECT-TYPE
	     	SYNTAX	INTEGER
	     	MAX-ACCESS	read-only
	     	STATUS		current
	     	DESCRIPTION
	     	"
	     		G.口最近第几个24小时的LOSW秒数
	     	"
            ::= { rcftSHDSLPortIntervalDayEntry 9 }

	 	rcftSHDSLPortIntervalDayLOFTimes OBJECT-TYPE
	     	SYNTAX	INTEGER
	     	MAX-ACCESS	read-only
	     	STATUS		current
	     	DESCRIPTION
	     	"
	     		G.口最近第几个24小时的LOSW次数
	     	"
            ::= { rcftSHDSLPortIntervalDayEntry 10 }

	 	rcftSHDSLPortIntervalDayCRCTimes OBJECT-TYPE
	     	SYNTAX	INTEGER
	     	MAX-ACCESS	read-only
	     	STATUS		current
	     	DESCRIPTION
	     	"
	     		G.口最近第几个24小时的LOSW次数
	     	"
            ::= { rcftSHDSLPortIntervalDayEntry 11 }


    -----------G.口的告警---------------------

      rcftSHDSLPortLOSTrap	NOTIFICATION-TYPE
      	OBJECTS{
			rcftSHDSLPortAlarmStatus
      	}
      	STATUS current
     	DESCRIPTION
     	"
     		局端设备上G.口的LOS告警
     	"
     	::= { rcftSHDSLPortTraps 1 }

      rcftSHDSLPortLOSWTrap	NOTIFICATION-TYPE
      	OBJECTS{
			rcftSHDSLPortAlarmStatus
      	}
      	STATUS current
     	DESCRIPTION
     	"
     		局端设备上G.口的LOSW告警
     	"
     	::= { rcftSHDSLPortTraps 2 }

      rcftSHDSLPortLINKTrap	NOTIFICATION-TYPE
      	OBJECTS{
			rcftSHDSLPortAlarmStatus
      	}
      	STATUS current
     	DESCRIPTION
     	"
     		局端设备上G.口的LINK告警
     	"
     	::= { rcftSHDSLPortTraps 3 }

      rcftSHDSLPortFECTrap	NOTIFICATION-TYPE
      	OBJECTS{
			rcftSHDSLPortAlarmStatus
      	}
      	STATUS current
     	DESCRIPTION
     	"
     		局端设备上G.口的FEC告警
     	"
     	::= { rcftSHDSLPortTraps 4 }

      rcftSHDSLPortCRCTrap	NOTIFICATION-TYPE
      	OBJECTS{
			rcftSHDSLPortAlarmStatus
      	}
      	STATUS current
     	DESCRIPTION
     	"
     		局端设备上G.口的CRC告警
     	"
     	::= { rcftSHDSLPortTraps 5 }

      rcftSHDSLPortSNRThresholdTrap	NOTIFICATION-TYPE
      	OBJECTS{
			rcftSHDSLPortSNRThreshold
      	}
      	STATUS current
     	DESCRIPTION
     	"
     		局端设备上G.口的CRC告警
     	"
     	::= { rcftSHDSLPortTraps 6 }


      rcftSHDSLPortAttenuationThresholdTrap	NOTIFICATION-TYPE
      	OBJECTS{
			rcftSHDSLPortAttenuationThreshold
      	}
      	STATUS current
     	DESCRIPTION
     	"
     		局端设备上G.口的CRC告警
     	"
     	::= { rcftSHDSLPortTraps 7 }


      rcftSHDSLPortLOSThresholdTrap	NOTIFICATION-TYPE
      	OBJECTS{
			rcftSHDSLPortLOSThreshold
      	}
      	STATUS current
     	DESCRIPTION
     	"
     		局端设备上G.口的CRC告警
     	"
     	::= { rcftSHDSLPortTraps 8 }

       rcftSHDSLPortLOSWThresholdTrap NOTIFICATION-TYPE
      	OBJECTS{
			rcftSHDSLPortLOSWThreshold
      	}
      	STATUS current
     	DESCRIPTION
     	"
     		局端设备上G.口的CRC告警
     	"
     	::= { rcftSHDSLPortTraps 9 }


       rcftSHDSLPortLOLKThresholdTrap NOTIFICATION-TYPE
      	OBJECTS{
			rcftSHDSLPortLOLKThreshold
      	}
      	STATUS current
     	DESCRIPTION
     	"
     		局端设备上G.口的CRC告警
     	"
     	::= { rcftSHDSLPortTraps 10 }

       rcftSHDSLPortESThresholdTrap NOTIFICATION-TYPE
      	OBJECTS{
			rcftSHDSLPortESThreshold
      	}
      	STATUS current
     	DESCRIPTION
     	"
     		局端设备上G.口的CRC告警
     	"
     	::= { rcftSHDSLPortTraps 11 }

   --------------------------DS3E3端口的对象---------------------------------

   rcftDS3E3PortTable OBJECT-TYPE
       SYNTAX  SEQUENCE OF RcftDS3E3PortEntry
       MAX-ACCESS  not-accessible
       STATUS  current
       DESCRIPTION
       "
         The DS3E3 PORT table.
       "
       ::= { rcftDS3E3PortObjects 1 }

    rcftDS3E3PortEntry OBJECT-TYPE
       SYNTAX  RcftDS3E3PortEntry
       MAX-ACCESS  not-accessible
       STATUS  current
       DESCRIPTION
       "
          An entry in the DS3E3 PORT table.

       "
       INDEX   { rcftChassisIndex, rcftSlotIndex,rcftDS3E3PortIndex }
       ::= { rcftDS3E3PortTable 1 }


    RcftDS3E3PortEntry ::=
       SEQUENCE {
       rcftDS3E3PortIndex		 	Integer32,
       rcftDS3E3PortAlarmStatus		INTEGER,
       rcftDS3E3PortStatus			INTEGER,
       rcftDS3E3PortESCont			INTEGER,
       rcftDS3E3PortLoopStatus		INTEGER,
       rcftDS3E3PortOrder			INTEGER
       }

    rcftDS3E3PortIndex OBJECT-TYPE
    	SYNTAX	   Integer32
    	MAX-ACCESS read-only
    	STATUS		current
    	DESCRIPTION
    	"
    		DS3E3口的索引
    	"
        ::= { rcftDS3E3PortEntry 1 }

    rcftDS3E3PortAlarmStatus	OBJECT-TYPE
    	SYNTAX	INTEGER
    	MAX-ACCESS read-only
    	STATUS		current
    	DESCRIPTION
    	"
    		BIT24	OOF    从本地设备上看对端设备电口帧失步告警		 	1：正常    0：告警
            BIT23	RAI	   从本地设备上看对端设备RAI告警    			1:	正常	0：告警
    		BIT22   LOF    从本地设备上看对端设备电口帧丢失告警         1: 正常    0: 告警
    		BIT21	CRC	   从本地设备上看对端设备电口CRC校验错告警      1：正常	   0：告警
			BIT20   RLCV   从本地设备上看对端设备电口编码冲突告警       1：正常    0：告警
			BIT19   RDMO   从本地设备上看对端设备电口发送信号无输出     1：正常    0：告警
			BIT18   RLOL   从本地设备上看对端设备电口接收信号失锁告警   1：正常    0：告警
			BIT17   RLOS   从本地设备上看对端设备电口接收信号丢失告警   1：正常    0：告警
			BIT16   RAIS   从本地设备上看对端设备电口接收信号AIS 告警   1：正常    0：告警

            BIT8	OOF   帧失步告警		 1：正常    0：告警
            BIT7	RAI	  RAI告警			 1:	正常	0：告警
    	    BIT6    LOF	  帧丢失告警         1: 正常    0: 告警
    	    BIT5	CRC	  CRC校验错告警      1：正常	0：告警
			BIT4    LCV   编码冲突告警       1：正常    0：告警
			BIT3    DMO   发送信号无输出     1：正常    0：告警
			BIT2    LOL   接收信号失锁告警   1：正常    0：告警
			BIT1    LOS   接收信号丢失告警   1：正常    0：告警
			BIT0    AIS   接收信号AIS 告警   1：正常    0：告警
    	"
        ::= { rcftDS3E3PortEntry 2 }


	rcftDS3E3PortStatus		OBJECT-TYPE
		SYNTAX	INTEGER
		MAX-ACCESS read-write
		STATUS	current
		DESCRIPTION
		"
			 BIT10:  线路编码
			 		0:AMI
			 		1:B3ZS		--------------DS3
			 		1:HDB3      --------------E3
			 BIT9-8：帧结构:
			 		00:G.751	01:G.832   ------------E3
			 		00:M23		01:C-bit   ------------DS3

			 BIT7: 是否成帧				1: 成帧,	 0:非成帧
			 BIT6: DS3/E3传输距离		1：长距，	 0：短距
			 BIT5：保留
			 BIT4：DS3/E3误码仪状态，   1：打开，0：关闭
			 BIT3：FaultPass故障转移    1：使能，0：禁止

			 BIT2-1 端口的环回状态： 0：无环回，1：内环，2：外环，3：双向环
		     BIT0   端口模式选择     0：E3    1：DS3
		"
		::= { rcftDS3E3PortEntry 3 }

	rcftDS3E3PortESCont	  OBJECT-TYPE
		SYNTAX  INTEGER
		MAX-ACCESS	read-only
		STATUS  current
		DESCRIPTION
		"
			误码秒个数
		"
        ::= { rcftDS3E3PortEntry 4 }




	rcftDS3E3PortLoopStatus		OBJECT-TYPE
		SYNTAX	INTEGER
		MAX-ACCESS read-only
		STATUS	current
		DESCRIPTION
		"
		    1:本地环回，
			2：无本地环回，
			3：远端环回，
			4：无远端环回，
			5: 无环回，
			6：本地内环使能，
			7：本地外环使能，
			8：本地双向环使能，
			9：远端内环使能，
			10：远端外环使能，
			11：远端双向环使能，
			12：本地内环禁止，
			13: 本地外环禁止，
			14：本地双向环禁止，
			15：远端内环禁止，
			16：远端外环禁止，
			17：远端双向环禁止
		"
		::= { rcftDS3E3PortEntry 5 }

	rcftDS3E3PortOrder	  OBJECT-TYPE
		SYNTAX	INTEGER
		MAX-ACCESS read-write
		STATUS  current
		DESCRIPTION
		"
			    1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
 				22: 端口BERT测试开始
 				23: 端口BERT测试结束
				24：统计信息清零
				25：告警屏蔽
				26：告警屏蔽解除
				27：端口未用支路告警屏蔽
				28：端口未用支路告警屏蔽解除
				29：环回检测使能
				30：环回检测停止
				31：开始查询SFP扩展信息
				32；停止查询SFP扩展信息
				33：开始查询SFP数字诊断信息
				34：停止查询SFP数字诊断信息
				注：31-34尚没有对网管开放


			注意：对于约定5，枚举值5-9废弃，
		    rcftDS3E3PortOrder的枚举值要和其他接口级命令节点始终保持完全一致。
		"
	    ::= { rcftDS3E3PortEntry 6 }

	   --------------------------DS3E3电口的流量统计--------------------------

         rcftDS3E3StatisticTable OBJECT-TYPE
	        SYNTAX SEQUENCE OF RcftDS3E3StatisticEntry
	        MAX-ACCESS not-accessible
	        STATUS current
	        DESCRIPTION
	          "
	          局端设备DS3E3端口的统计表.
	          "
            ::= {rcftDS3E3PortPerformance 1}

	    rcftDS3E3StatisticEntry OBJECT-TYPE
	        SYNTAX RcftDS3E3StatisticEntry
	        MAX-ACCESS not-accessible
	        STATUS current
	        DESCRIPTION
	          "
	             以rcftDS3E3Index为索引
	          "
	        AUGMENTS { rcftDS3E3PortEntry }
	        ::= {rcftDS3E3StatisticTable 1}

	    RcftDS3E3StatisticEntry ::= SEQUENCE {
				rcftDS3E3TxPackets         Counter32,
				rcftDS3E3TxBytes           Counter32,
				rcftDS3E3TxFailurePackets  Counter32,
				rcftDS3E3RxPackets         Counter32,
				rcftDS3E3RxBytes           Counter32,
				rcftDS3E3RxErrorPackets    Counter32,
				rcftDS3E3FluxTimer		   Counter32
	         }


    	  rcftDS3E3TxPackets OBJECT-TYPE
					SYNTAX Counter32
					MAX-ACCESS read-only
					STATUS current
					DESCRIPTION
						"
							DS3E3口发送以太网包数
						"
					::= { rcftDS3E3StatisticEntry 1 }

		 rcftDS3E3TxBytes OBJECT-TYPE
					SYNTAX Counter32
					MAX-ACCESS read-only
					STATUS current
					DESCRIPTION
						"
							DS3E3口发送以太网字节数
						"
					::= { rcftDS3E3StatisticEntry 2 }


	    rcftDS3E3TxFailurePackets OBJECT-TYPE
					SYNTAX Counter32
					MAX-ACCESS read-only
					STATUS current
					DESCRIPTION
						"
							DS3E3电口发送以太网丢包数
						"
					::= { rcftDS3E3StatisticEntry 3 }

		 rcftDS3E3RxPackets OBJECT-TYPE
					SYNTAX Counter32
					MAX-ACCESS read-only
					STATUS current
					DESCRIPTION
						"
							DS3E3口接收以太网包数
						"
					::= { rcftDS3E3StatisticEntry 4 }

		 rcftDS3E3RxBytes OBJECT-TYPE
					SYNTAX Counter32
					MAX-ACCESS read-only
					STATUS current
					DESCRIPTION
						"
							DS3E3口接收以太网字节数
						"
					::= { rcftDS3E3StatisticEntry 5 }

	    rcftDS3E3RxErrorPackets OBJECT-TYPE
					SYNTAX Counter32
					MAX-ACCESS read-only
					STATUS current
					DESCRIPTION
						"
							DS3E3电口接收以太网丢包数
						"
					::= { rcftDS3E3StatisticEntry 6 }

        rcftDS3E3FluxTimer	OBJECT-TYPE
        			SYNTAX		Counter32
        			MAX-ACCESS 	read-only
        			STATUS		current
        			DESCRIPTION
        				"
        					流量统计的时间
        				"
                    ::= { rcftDS3E3StatisticEntry 7 }



    --------------------------DS3E3端口的告警------------------------

       rcftDS3E3PortAISTrap	NOTIFICATION-TYPE
      	OBJECTS{
			rcftDS3E3PortAlarmStatus
      	}
      	STATUS current
     	DESCRIPTION
     	"
     		局端设备上DS3E3端口的接收信号AIS告警
     	"
     	::= { rcftDS3E3PortTraps 1 }


       rcftDS3E3PortLOSTrap	NOTIFICATION-TYPE
      	OBJECTS{
			rcftDS3E3PortAlarmStatus
      	}
      	STATUS current
     	DESCRIPTION
     	"
     		局端设备上DS3E3端口的接收信号丢失告警
     	"
     	::= { rcftDS3E3PortTraps 2 }


       rcftDS3E3PortLOLTrap	NOTIFICATION-TYPE
      	OBJECTS{
			rcftDS3E3PortAlarmStatus
      	}
      	STATUS current
     	DESCRIPTION
     	"
     		局端设备上DS3E3端口的接收信号失锁告警
     	"
     	::= { rcftDS3E3PortTraps 3 }


       rcftDS3E3PortDMOTrap	NOTIFICATION-TYPE
      	OBJECTS{
			rcftDS3E3PortAlarmStatus
      	}
      	STATUS current
     	DESCRIPTION
     	"
     		局端设备上DS3E3端口的发送信号无输出告警
     	"
     	::= { rcftDS3E3PortTraps 4 }

       rcftDS3E3PortCVTrap	NOTIFICATION-TYPE
      	OBJECTS{
			rcftDS3E3PortAlarmStatus
      	}
      	STATUS current
     	DESCRIPTION
     	"
     		局端设备上DS3E3端口的编码冲突告警
     	"
     	::= { rcftDS3E3PortTraps 5 }

       rcftDS3E3PortCRCTrap	NOTIFICATION-TYPE
      	OBJECTS{
			rcftDS3E3PortAlarmStatus
      	}
      	STATUS current
     	DESCRIPTION
     	"
     		局端设备上DS3E3端口的CRC告警
     	"
     	::= { rcftDS3E3PortTraps 6 }
       rcftDS3E3PortToRAISTrap	NOTIFICATION-TYPE
      	OBJECTS{
			rcftDS3E3PortAlarmStatus
      	}
      	STATUS current
     	DESCRIPTION
     	"
     		从本地设备上看对端设备电口接收信号AIS 告警
     	"
     	::= { rcftDS3E3PortTraps 7 }


       rcftDS3E3PortToRLOSTrap	NOTIFICATION-TYPE
      	OBJECTS{
			rcftDS3E3PortAlarmStatus
      	}
      	STATUS current
     	DESCRIPTION
     	"
     		从本地设备上看对端设备电口接收信号LOS 告警
     	"
     	::= { rcftDS3E3PortTraps 8 }


       rcftDS3E3PortToRLOLTrap	NOTIFICATION-TYPE
      	OBJECTS{
			rcftDS3E3PortAlarmStatus
      	}
      	STATUS current
     	DESCRIPTION
     	"
     		从本地设备上看对端设备电口接收信号LOL 告警
     	"
     	::= { rcftDS3E3PortTraps 9 }


       rcftDS3E3PortToRDMOTrap	NOTIFICATION-TYPE
      	OBJECTS{
			rcftDS3E3PortAlarmStatus
      	}
      	STATUS current
     	DESCRIPTION
     	"
     		从本地设备上看对端设备电口发送信号无输出告警
     	"
     	::= { rcftDS3E3PortTraps 10 }

       rcftDS3E3PortToRCVTrap	NOTIFICATION-TYPE
      	OBJECTS{
			rcftDS3E3PortAlarmStatus
      	}
      	STATUS current
     	DESCRIPTION
     	"
     		从本地设备上看对端设备电口编码冲突告警
     	"
     	::= { rcftDS3E3PortTraps 11 }

      rcftDS3E3PortToRCRCTrap	NOTIFICATION-TYPE
      	OBJECTS{
			rcftDS3E3PortAlarmStatus
      	}
      	STATUS current
     	DESCRIPTION
     	"
     		从本地设备上看对端设备电口CRC告警
     	"
     	::= { rcftDS3E3PortTraps 12 }

      rcftDS3E3PortLOFTrap	NOTIFICATION-TYPE
      	OBJECTS{
			rcftDS3E3PortAlarmStatus
      	}
      	STATUS current
     	DESCRIPTION
     	"
     		局端设备上DS3E3端口的LOF告警
     	"
     	::= { rcftDS3E3PortTraps 13 }

        rcftDS3E3PortToRLOFTrap	NOTIFICATION-TYPE
      	OBJECTS{
			rcftDS3E3PortAlarmStatus
      	}
      	STATUS current
     	DESCRIPTION
     	"
     		从本地设备上看对端设备电口LOF告警
     	"
     	::= { rcftDS3E3PortTraps 14 }

     	rcftDS3E3PortRAITrap	NOTIFICATION-TYPE
      	OBJECTS{
			rcftDS3E3PortAlarmStatus
      	}
      	STATUS current
     	DESCRIPTION
     	"
     		局端设备上DS3E3端口的RAI告警
     	"
     	::= { rcftDS3E3PortTraps 15 }

        rcftDS3E3PortToRRAITrap	NOTIFICATION-TYPE
      	OBJECTS{
			rcftDS3E3PortAlarmStatus
      	}
      	STATUS current
     	DESCRIPTION
     	"
     		从本地设备上看对端设备电口RAI告警
     	"
     	::= { rcftDS3E3PortTraps 16 }

        rcftDS3E3PortOOFTrap	NOTIFICATION-TYPE
      	OBJECTS{
			rcftDS3E3PortAlarmStatus
      	}
      	STATUS current
     	DESCRIPTION
     	"
     		局端设备上DS3E3端口的OOF告警
     	"
     	::= { rcftDS3E3PortTraps 17 }

        rcftDS3E3PortToROOFTrap	NOTIFICATION-TYPE
      	OBJECTS{
			rcftDS3E3PortAlarmStatus
      	}
      	STATUS current
     	DESCRIPTION
     	"
     		从本地设备上看对端设备电口OOF告警
     	"
     	::= { rcftDS3E3PortTraps 18 }

     --------------------------DS1端口的对象---------------------------------

   rcftDS1PortTable OBJECT-TYPE
       SYNTAX  SEQUENCE OF RcftDS1PortEntry
       MAX-ACCESS  not-accessible
       STATUS  current
       DESCRIPTION
       "
         The DS1 PORT table.
       "
       ::= { rcftDS1PortObjects 1 }

    rcftDS1PortEntry OBJECT-TYPE
       SYNTAX  RcftDS1PortEntry
       MAX-ACCESS  not-accessible
       STATUS  current
       DESCRIPTION
       "
          An entry in the DS1 PORT table.

       "
       INDEX   { rcftChassisIndex, rcftSlotIndex,rcftDS1PortIndex }
       ::= { rcftDS1PortTable 1 }


    RcftDS1PortEntry ::=
       SEQUENCE {
       rcftDS1PortIndex		 	Integer32,
       rcftDS1PortAlarmStatus		INTEGER,
       rcftDS1PortStatus			INTEGER,
       rcftDS1PortBertStatus		INTEGER,
       rcftDS1PortESCont			INTEGER,
       rcftDS1PortSESCont			INTEGER,
       rcftDS1PortLoopStatus		INTEGER,
       rcftDS1PortOrder			INTEGER,
       rcftDS1PortTranLength		INTEGER,
       rcftDS1PortFaultPassIndicator	INTEGER,
       rcftDS1PortframeType		INTEGER,
       rcftDS1PortChannel	INTEGER
       }

    rcftDS1PortIndex OBJECT-TYPE
    	SYNTAX	   Integer32
    	MAX-ACCESS read-only
    	STATUS		current
    	DESCRIPTION
    	"
    		DS1口的索引
    	"
        ::= { rcftDS1PortEntry 1 }

    rcftDS1PortAlarmStatus	OBJECT-TYPE
    	SYNTAX	INTEGER
    	MAX-ACCESS read-only
    	STATUS		current
    	DESCRIPTION
    	"
    		BIT22	LOF	   从本地设备上看对端DS1电口的LOF	            1：正常	   0：告警
    		BIT21	CRC	   从本地设备上看对端设备电口CRC校验错告警      1：正常	   0：告警
			BIT20   RLCV   从本地设备上看对端设备电口编码冲突告警       1：正常    0：告警
			BIT19   RDMO   从本地设备上看对端设备电口发送信号无输出     1：正常    0：告警
			BIT18   RLOL   从本地设备上看对端设备电口接收信号失锁告警   1：正常    0：告警
			BIT17   RLOS   从本地设备上看对端设备电口接收信号丢失告警   1：正常    0：告警
			BIT16   RAIS   从本地设备上看对端设备电口接收信号AIS 告警   1：正常    0：告警

    	    BIT8	RED						  1:正常    0：告警
    	 	BIT7    YEL   					  1:正常    0：告警
    	    BIT6	LOF   接收信号帧失步告警  1：正常	0：告警
    	    BIT5	CRC	  CRC校验错告警      1：正常	0：告警
			BIT4    LCV   编码冲突告警       1：正常    0：告警
			BIT3    DMO   发送信号无输出     1：正常    0：告警
			BIT2    LOL   接收信号失锁告警   1：正常    0：告警
			BIT1    LOS   接收信号丢失告警   1：正常    0：告警
			BIT0    AIS   接收信号AIS 告警   1：正常    0：告警
    	"
        ::= { rcftDS1PortEntry 2 }


	rcftDS1PortStatus		OBJECT-TYPE
		SYNTAX	INTEGER
		MAX-ACCESS read-write
		STATUS	current
		DESCRIPTION
		"
			BIT0：线路编码类型   1:B8ZS       0:AMI
			BIT1: 故障转移		 1：使能      0：禁止
			BIT2: DS1是否成帧	 1：成帧	  0：非成帧
			BIT3: ds1是否打开,	 1:打开		  0:关闭
		"
		::= { rcftDS1PortEntry 3 }

	rcftDS1PortBertStatus	OBJECT-TYPE
		SYNTAX INTEGER
		MAX-ACCESS	read-only
		STATUS	current
		DESCRIPTION
		"
			BIT0   DS1误码仪状态，   1：打开，0：关闭

		"
		::= { rcftDS1PortEntry 4 }


	rcftDS1PortESCont	  OBJECT-TYPE
		SYNTAX  INTEGER
		MAX-ACCESS	read-only
		STATUS  current
		DESCRIPTION
		"
			误码秒个数
		"
        ::= { rcftDS1PortEntry 5 }

    rcftDS1PortSESCont     OBJECT-TYPE
		SYNTAX  INTEGER
		MAX-ACCESS	read-only
		STATUS  current
		DESCRIPTION
		"
			严重误码秒个数
		"
        ::= { rcftDS1PortEntry 6 }

	rcftDS1PortLoopStatus		OBJECT-TYPE
		SYNTAX	INTEGER
		MAX-ACCESS read-only
		STATUS	current
		DESCRIPTION
		"
		    1:本地环回，
			2：无本地环回，
			3：远端环回，
			4：无远端环回，
			5: 无环回，
			6：本地内环使能，
			7：本地外环使能，
			8：本地双向环使能，
			9：远端内环使能，
			10：远端外环使能，
			11：远端双向环使能，
			12：本地内环禁止，
			13: 本地外环禁止，
			14：本地双向环禁止，
			15：远端内环禁止，
			16：远端外环禁止，
			17：远端双向环禁止
		"
		::= { rcftDS1PortEntry 7 }

	rcftDS1PortOrder	  OBJECT-TYPE
		SYNTAX	INTEGER
		MAX-ACCESS read-write
		STATUS  current
		DESCRIPTION
		"
		 	1：硬复位
			2：软复位
			3：开始查询统计信息
			4：结束查询统计信息
			5：内环使能
			6：内环禁止
			7：外环使能
			8：外环禁止
			9: 无环回
			10: 本地内环使能
			11: 本地外环使能
			12: 本地双向环使能
			13: 远端内环使能
			14: 远端外环使能
			15: 远端双向环使能
			16: 本地内环禁止
			17: 本地外环禁止
			18: 本地双向环禁止
			19: 远端内环禁止
			20: 远端外环禁止
			21: 远端双向环禁止
			22: 端口BERT测试开始
			23: 端口BERT测试结束
		"
	    ::= { rcftDS1PortEntry 8 }

	rcftDS1PortTranLength	OBJECT-TYPE
	    SYNTAX	INTEGER
		MAX-ACCESS read-write
		STATUS  current
		DESCRIPTION
		"
		      DS1  传输距离

		    2：短距，DS1传输距离为0~133ft
			3：短距，DS1传输距离为133~266ft
			4：短距，DS1传输距离为266~399ft
			5：短距，DS1传输距离为399~533ft
			6：短距，DS1传输距离为533~655ft
			8：长距，0dB
			9：长距，-7.5dB
			10：长距，-15.0dB
			11：长距，-22.5dB

		"
		::= { rcftDS1PortEntry 9 }

	rcftDS1PortFaultPassIndicator OBJECT-TYPE
		SYNTAX  INTEGER
		MAX-ACCESS read-only
		STATUS  current
		DESCRIPTION
		"
			DS1故障转移指示灯
			１：灭，故障转移禁止
			２：绿常亮，故障转移使能，但没有故障发生
			３：黄闪亮，故障转移使能，且发生故障导致以太口关闭
		"
		::= { rcftDS1PortEntry 10 }

	rcftDS1PortframeType	OBJECT-TYPE
		SYNTAX  INTEGER
		MAX-ACCESS read-write
		STATUS  current
		DESCRIPTION
		"
		DS1帧格式
		1：SF帧格式
		2：ESF
		3：DM
		4：SLC-96
		"
		::= { rcftDS1PortEntry 11 }


    rcftDS1PortChannel	OBJECT-TYPE
		SYNTAX  INTEGER
		MAX-ACCESS read-write
		STATUS  current
		DESCRIPTION
		"
		DS1成帧时所用的时隙，bit0-bit323每位分别表示时隙１到24的占用情况。
		"
        ::= { rcftDS1PortEntry 12 }

		  --------------------------DS1电口的流量统计--------------------------

         rcftDS1StatisticTable OBJECT-TYPE
	        SYNTAX SEQUENCE OF RcftDS1StatisticEntry
	        MAX-ACCESS not-accessible
	        STATUS current
	        DESCRIPTION
	          "
	          局端设备DS1端口的统计表.
	          "
            ::= {rcftDS1PortPerformance 1}

	    rcftDS1StatisticEntry OBJECT-TYPE
	        SYNTAX RcftDS1StatisticEntry
	        MAX-ACCESS not-accessible
	        STATUS current
	        DESCRIPTION
	          "
	             以rcftDS1Index为索引
	          "
	        AUGMENTS { rcftDS1PortEntry }
	        ::= {rcftDS1StatisticTable 1}

	    RcftDS1StatisticEntry ::= SEQUENCE {
				rcftDS1PortTxPackets         Counter32,
				rcftDS1PortTxBytes           Counter32,
				rcftDS1PortTxFailurePackets  Counter32,
				rcftDS1PortRxPackets         Counter32,
				rcftDS1PortRxBytes           Counter32,
				rcftDS1PortRxErrorPackets    Counter32,
				rcftDS1PortFluxTimer		   Counter32
	         }


    	  rcftDS1PortTxPackets OBJECT-TYPE
					SYNTAX Counter32
					MAX-ACCESS read-only
					STATUS current
					DESCRIPTION
						"
							DS1口发送以太网包数
						"
					::= { rcftDS1StatisticEntry 1 }

		 rcftDS1PortTxBytes OBJECT-TYPE
					SYNTAX Counter32
					MAX-ACCESS read-only
					STATUS current
					DESCRIPTION
						"
							DS1口发送以太网字节数
						"
					::= { rcftDS1StatisticEntry 2 }


	    rcftDS1PortTxFailurePackets OBJECT-TYPE
					SYNTAX Counter32
					MAX-ACCESS read-only
					STATUS current
					DESCRIPTION
						"
							DS1电口发送以太网丢包数
						"
					::= { rcftDS1StatisticEntry 3 }

		 rcftDS1PortRxPackets OBJECT-TYPE
					SYNTAX Counter32
					MAX-ACCESS read-only
					STATUS current
					DESCRIPTION
						"
							DS1口接收以太网包数
						"
					::= { rcftDS1StatisticEntry 4 }

		 rcftDS1PortRxBytes OBJECT-TYPE
					SYNTAX Counter32
					MAX-ACCESS read-only
					STATUS current
					DESCRIPTION
						"
							DS1口接收以太网字节数
						"
					::= { rcftDS1StatisticEntry 5 }

	    rcftDS1PortRxErrorPackets OBJECT-TYPE
					SYNTAX Counter32
					MAX-ACCESS read-only
					STATUS current
					DESCRIPTION
						"
							DS1电口接收以太网错误包数						"
					::= { rcftDS1StatisticEntry 6 }

        rcftDS1PortFluxTimer	OBJECT-TYPE
        			SYNTAX		Counter32
        			MAX-ACCESS 	read-only
        			STATUS		current
        			DESCRIPTION
        				"
        					流量统计的时间
        				"
                    ::= { rcftDS1StatisticEntry 7 }




	 --------------------------DS1端口的告警------------------------

       rcftDS1PortAISTrap	NOTIFICATION-TYPE
      	OBJECTS{
			rcftDS1PortAlarmStatus
      	}
      	STATUS current
     	DESCRIPTION
     	"
     		局端设备上DS1端口的接收信号AIS告警
     	"
     	::= { rcftDS1PortTraps 1 }


       rcftDS1PortLOSTrap	NOTIFICATION-TYPE
      	OBJECTS{
			rcftDS1PortAlarmStatus
      	}
      	STATUS current
     	DESCRIPTION
     	"
     		局端设备上DS1端口的接收信号丢失告警
     	"
     	::= { rcftDS1PortTraps 2 }

       rcftDS1PortToRAISTrap	NOTIFICATION-TYPE
      	OBJECTS{
			rcftDS1PortAlarmStatus
      	}
      	STATUS current
     	DESCRIPTION
     	"
     		局端设备上DS1端口的接收对端信号AIS告警
     	"
     	::= { rcftDS1PortTraps 3 }


       rcftDS1PortToRLOSTrap	NOTIFICATION-TYPE
      	OBJECTS{
			rcftDS1PortAlarmStatus
      	}
      	STATUS current
     	DESCRIPTION
     	"
     		局端设备上DS1端口的接收对端信号丢失告警
     	"
     	::= { rcftDS1PortTraps 4 }

       rcftDS1PortLOFTrap	NOTIFICATION-TYPE
      	OBJECTS{
			rcftDS1PortAlarmStatus
      	}
      	STATUS current
     	DESCRIPTION
     	"
     		局端设备上DS1端口信号帧失步LOF告警
     	"
     	::= { rcftDS1PortTraps 5 }

		 rcftDS1PortCRCTrap	NOTIFICATION-TYPE
      	OBJECTS{
			rcftDS1PortAlarmStatus
      	}
      	STATUS current
     	DESCRIPTION
     	"
     		局端设备上DS1端口信号CRC校验错告警
     	"
     	::= { rcftDS1PortTraps 6 }

        rcftDS1PortToRLOFTrap	NOTIFICATION-TYPE
      	OBJECTS{
			rcftDS1PortAlarmStatus
      	}
      	STATUS current
     	DESCRIPTION
     	"
     		局端设备上DS1端口接收对端信号帧失步LOF告警
     	"
     	::= { rcftDS1PortTraps 7 }

		 rcftDS1PortToRCRCTrap	NOTIFICATION-TYPE
      	OBJECTS{
			rcftDS1PortAlarmStatus
      	}
      	STATUS current
     	DESCRIPTION
     	"
     		局端设备上DS1端口信号接收对端CRC校验错告警
     	"
     	::= { rcftDS1PortTraps 8 }

     	 rcftDS1PortFaultPassIndicatorTrap	NOTIFICATION-TYPE
      	OBJECTS{
			rcftDS1PortFaultPassIndicator
      	}
      	STATUS current
     	DESCRIPTION
     	"
     		局端设备上DS1端口信号故障转移指示灯告警
     	"
     	::= { rcftDS1PortTraps 9 }

	     rcftDS1PortDMOTrap	NOTIFICATION-TYPE
      	OBJECTS{
			rcftDS1PortAlarmStatus
      	}
      	STATUS current
     	DESCRIPTION
     	"
     		局端设备上DS1端口的接收信号DMO告警
     	"
     	::= { rcftDS1PortTraps 10 }


       rcftDS1PortCVTrap	NOTIFICATION-TYPE
      	OBJECTS{
			rcftDS1PortAlarmStatus
      	}
      	STATUS current
     	DESCRIPTION
     	"
     		局端设备上DS1端口的CV告警
     	"
     	::= { rcftDS1PortTraps 11 }

       rcftDS1PortYELTrap	NOTIFICATION-TYPE
      	OBJECTS{
			rcftDS1PortAlarmStatus
      	}
      	STATUS current
     	DESCRIPTION
     	"
     		局端设备上DS1端口的YEL告警
     	"
     	::= { rcftDS1PortTraps 12 }


       rcftDS1PortREDTrap	NOTIFICATION-TYPE
      	OBJECTS{
			rcftDS1PortAlarmStatus
      	}
      	STATUS current
     	DESCRIPTION
     	"
     		局端设备上DS1端口的RED告警
     	"
     	::= { rcftDS1PortTraps 13 }


  	 rcftAudioPortTable OBJECT-TYPE
       SYNTAX  SEQUENCE OF RcftAudioPortEntry
       MAX-ACCESS  not-accessible
       STATUS  current
       DESCRIPTION
       "
         The Audio PORT table.
       "
       ::= { rcftAudioPortObjects 1 }

     rcftAudioPortEntry OBJECT-TYPE
       SYNTAX  RcftAudioPortEntry
       MAX-ACCESS  not-accessible
       STATUS  current
       DESCRIPTION
       "
          An entry in the Audio PORT table.

       "
       INDEX   { rcftChassisIndex, rcftSlotIndex,rcftAudioPortIndex }
       ::= { rcftAudioPortTable 1 }


    RcftAudioPortEntry ::=
       SEQUENCE {
       rcftAudioPortIndex		 	Integer32,
       rcftAudioPortStatus			INTEGER,
       rcftAudioPortPosition		INTEGER,
       rcftAudioPortType		INTEGER
       }

    rcftAudioPortIndex OBJECT-TYPE
    	SYNTAX	   Integer32
    	MAX-ACCESS read-only
    	STATUS		current
    	DESCRIPTION
    	"
    		Audio口的索引
    	"
        ::= { rcftAudioPortEntry 1 }

    rcftAudioPortStatus	OBJECT-TYPE
    	SYNTAX	INTEGER
    	MAX-ACCESS read-write
    	STATUS		current
    	DESCRIPTION
    	"
			BIT1    LOS  音频口有无信号告警   	1：正常    	0：告警
			BIT0	音频口的开关状态	        0：关闭		1：打开

    	"
        ::= { rcftAudioPortEntry 2 }

      rcftAudioPortPosition OBJECT-TYPE
    	SYNTAX INTEGER
    	MAX-ACCESS read-only
    	STATUS current
    	DESCRIPTION
    	"
    		音频口的位置信息：
    		bit7-4：盘
    		bit3-0：槽
    	"
    	::={ rcftAudioPortEntry 3}


      rcftAudioPortType OBJECT-TYPE
    	SYNTAX	INTEGER
    	MAX-ACCESS read-only
    	STATUS		current
    	DESCRIPTION
    	"
			音频口的类型：
			1：电话用户端
			2：电话中继端
			3：高保真双向音频
			4：高保真音频编码
			5：高保真音频解码
    	"
        ::= { rcftAudioPortEntry 4 }



   rcftVideoPortTable OBJECT-TYPE
       SYNTAX  SEQUENCE OF RcftVideoPortEntry
       MAX-ACCESS  not-accessible
       STATUS  current
       DESCRIPTION
       "
         The Video PORT table.
       "
       ::= { rcftVideoPortObjects 1 }

    rcftVideoPortEntry OBJECT-TYPE
       SYNTAX  RcftVideoPortEntry
       MAX-ACCESS  not-accessible
       STATUS  current
       DESCRIPTION
       "
          An entry in the Video PORT table.

       "
       INDEX   { rcftChassisIndex, rcftSlotIndex,rcftVideoPortIndex }
       ::= { rcftVideoPortTable 1 }


    RcftVideoPortEntry ::=
       SEQUENCE {
       rcftVideoPortIndex		 	Integer32,
       rcftVideoPortStatus			INTEGER,
       rcftVideoPortPosition		INTEGER,
       rcftVideoPortSourceID		INTEGER
       }

    rcftVideoPortIndex OBJECT-TYPE
    	SYNTAX	   Integer32
    	MAX-ACCESS read-only
    	STATUS		current
    	DESCRIPTION
    	"
    		Video口的索引
    	"
        ::= { rcftVideoPortEntry 1 }

    rcftVideoPortStatus	OBJECT-TYPE
    	SYNTAX	INTEGER
    	MAX-ACCESS read-write
    	STATUS		current
    	DESCRIPTION
    	"
			BIT7	视频口输入信号状态			0：无信号；	1：有信号
			BIT6	视频口输出信号状态			0：无信号；	1：有信号
			BIT5	视频口输入信号开关			0：关闭；	1：打开
			BIT4	视频口输出信号开关			0：关闭；	1：打开
			BIT3	视频口方向					0：单向；	1：双向
			BIT2	视频口的开关状态			0：关闭		1：打开
			BIT1	视频口的属性				0：输入， 	1：输出
			BIT0    LOS   视频口有无信号告警		0：正常；	1：告警
    	"
        ::= { rcftVideoPortEntry 2 }

      rcftVideoPortPosition OBJECT-TYPE
    	SYNTAX INTEGER
    	MAX-ACCESS read-only
    	STATUS current
    	DESCRIPTION
    	"
    		数据口的位置信息：
    		bit7-4：盘
    		bit3-0：槽
    	"
    	::={ rcftVideoPortEntry 3}


      rcftVideoPortSourceID OBJECT-TYPE
    	SYNTAX	INTEGER
    	MAX-ACCESS read-write
    	STATUS		current
    	DESCRIPTION
    	"
			视频源ID
    	"
        ::= { rcftVideoPortEntry 4 }

     --------------------------Video 视频口的告警------------------------

       rcftVideoPortSignalLosTrap	NOTIFICATION-TYPE
      	OBJECTS{
			rcftVideoPortStatus
      	}
      	STATUS current
     	DESCRIPTION
     	"
     		局端设备上Video 视频口有无信号告警
     	"
     	::= { rcftVideoPortTraps 1 }


        rcftVideoPortSignalInLosTrap	NOTIFICATION-TYPE
      	OBJECTS{
			rcftVideoPortStatus
      	}
      	STATUS current
     	DESCRIPTION
     	"
     		局端设备上Video 视频口输入有无信号告警
     	"
     	::= { rcftVideoPortTraps 2 }



        rcftVideoPortSignalOutLosTrap	NOTIFICATION-TYPE
      	OBJECTS{
			rcftVideoPortStatus
      	}
      	STATUS current
     	DESCRIPTION
     	"
     		局端设备上Video 视频口输出有无信号告警
     	"
     	::= { rcftVideoPortTraps 3 }



    rcftDataPortTable OBJECT-TYPE
       SYNTAX  SEQUENCE OF RcftDataPortEntry
       MAX-ACCESS  not-accessible
       STATUS  current
       DESCRIPTION
       "
         The Data PORT table.
       "
       ::= { rcftDataPortObjects 1 }

    rcftDataPortEntry OBJECT-TYPE
       SYNTAX  RcftDataPortEntry
       MAX-ACCESS  not-accessible
       STATUS  current
       DESCRIPTION
       "
          An entry in the Data PORT table.

       "
       INDEX   { rcftChassisIndex, rcftSlotIndex,rcftDataPortIndex }
       ::= { rcftDataPortTable 1 }


    RcftDataPortEntry ::=
       SEQUENCE {
       rcftDataPortIndex		 	Integer32,
       rcftDataPortStatus			INTEGER,
       rcftDataPortPosition		INTEGER,
       rcftDataPortType		INTEGER
       }

    rcftDataPortIndex OBJECT-TYPE
    	SYNTAX	   Integer32
    	MAX-ACCESS read-only
    	STATUS		current
    	DESCRIPTION
    	"
    		Data 口的索引
    	"
        ::= { rcftDataPortEntry 1 }

    rcftDataPortStatus	OBJECT-TYPE
    	SYNTAX	INTEGER
    	MAX-ACCESS read-write
    	STATUS		current
    	DESCRIPTION
    	"
			BIT1    数据口有无信号			   	1：正常    	0：告警
			BIT0	数据口的开关状态	        0：关闭		1：打开
    	"
        ::= { rcftDataPortEntry 2 }

    	rcftDataPortPosition OBJECT-TYPE
    	SYNTAX INTEGER
    	MAX-ACCESS read-only
    	STATUS current
    	DESCRIPTION
    	"
    		数据口的位置信息：
    		bit7-4：盘
    		bit3-0：槽
    	"
    	::={ rcftDataPortEntry 3}

       rcftDataPortType OBJECT-TYPE
    	SYNTAX	INTEGER
    	MAX-ACCESS read-only
    	STATUS		current
    	DESCRIPTION
    	"
			数据口类型：
			1：232
			2：422
			3：485
			4：开关量
    	"
        ::= { rcftDataPortEntry 4 }



    rcftSimpleModuleTable OBJECT-TYPE
       SYNTAX  SEQUENCE OF RcftSimpleModuleEntry
       MAX-ACCESS  not-accessible
       STATUS  current
       DESCRIPTION
       "
         The Data PORT table.
       "
       ::= { rcftSimpleModuleObjects 1 }

    rcftSimpleModuleEntry OBJECT-TYPE
       SYNTAX  RcftSimpleModuleEntry
       MAX-ACCESS  not-accessible
       STATUS  current
       DESCRIPTION
       "
          An entry in the SimpleModule table.

       "
       INDEX   { rcftChassisIndex, rcftSlotIndex,rcftSimpleModuleIndex }
       ::= { rcftSimpleModuleTable 1 }


    RcftSimpleModuleEntry ::=
       SEQUENCE {
       rcftSimpleModuleIndex		 	Integer32,
       rcftSimpleModuleExist		INTEGER,
       rcftSimpleModulePosition		INTEGER,
       rcftSimpleModuleStatus		INTEGER,
       rcftSimpleModuleType		INTEGER
       }

    rcftSimpleModuleIndex OBJECT-TYPE
    	SYNTAX	   Integer32
    	MAX-ACCESS read-only
    	STATUS		current
    	DESCRIPTION
    	"
    		SimpleModule 口的索引
    	"
        ::= { rcftSimpleModuleEntry 1 }

        rcftSimpleModuleExist OBJECT-TYPE
        SYNTAX INTEGER
        MAX-ACCESS read-only
        STATUS current
        DESCRIPTION
        "
        	simpleModule 小模块是否存在，1：存在，2：不存在
        "
        ::= {rcftSimpleModuleEntry 2}

    	rcftSimpleModulePosition OBJECT-TYPE
    	SYNTAX INTEGER
    	MAX-ACCESS read-only
    	STATUS current
    	DESCRIPTION
    	"
    		SimpleModule的位置信息：
    		bit7-4：盘
    		bit3-0：槽
    	"
    	::={ rcftSimpleModuleEntry 3}

    	rcftSimpleModuleStatus  OBJECT-TYPE
    	SYNTAX INTEGER
    	MAX-ACCESS read-write
    	STATUS current
    	DESCRIPTION
    	"
    		bit1:	1：智能小模块，0：非智能小模块
    		bit0:	1：打开，	   0：关闭
    	"
    	::={ rcftSimpleModuleEntry 4}


       rcftSimpleModuleType OBJECT-TYPE
    	SYNTAX	INTEGER
    	MAX-ACCESS read-only
    	STATUS		current
    	DESCRIPTION
    	"
			SimpleModule类型：

			对于非智能小模块：
			1   一路232
			2   两路232
			3   一路422
			4   一路485
			5   两路485
			6   以太网模块
			7   开关量
			8   电话用户端
			9   电话中继端
			10   两路高保真双向音频
			11   两路高保真音频编码
			12   两路高保真音频解码

			智能小模块：1000+x，为对应的非智能小模块类型。

    	"
        ::= { rcftSimpleModuleEntry 5 }

   --------------------------simple module trap------------------------

       rcftSimpleModuleShutDownTrap	NOTIFICATION-TYPE
      	OBJECTS{
			rcftSimpleModuleStatus
      	}
      	STATUS current
     	DESCRIPTION
     	"
     		1:小模块打开，2：小模块关闭
     	"
     	::= { rcftSimpleModuleTraps 1 }


     ---------------------- FPGA 流量统计 ----------------------
    rcftSlotStatisticTable OBJECT-TYPE
	        SYNTAX SEQUENCE OF RcftSlotStatisticEntry
	        MAX-ACCESS not-accessible
	        STATUS current
	        DESCRIPTION
	          "
	          局端设备 FPGA 侧的流量统计表.
	          "
            ::= {rcftSlotPerformance 1}

	    rcftSlotStatisticEntry OBJECT-TYPE
	        SYNTAX RcftSlotStatisticEntry
	        MAX-ACCESS not-accessible
	        STATUS current
	        DESCRIPTION
	          "
	             以rcftSlotVCGIndex为索引
	          "
	        INDEX   { rcftChassisIndex, rcftSlotIndex,rcftPortIndex }
       		::= { rcftSlotStatisticTable 1 }

	    RcftSlotStatisticEntry ::= SEQUENCE {
	    		rcftPortIndex			Integer32,
	    		rcftPortType			INTEGER,
				rcftRxPackets    		Counter32,
				rcftRxLosPackets        Counter32,
				rcftRxPreabErrPackets   Counter32,
				rcftRxFCSErrPackets     Counter32,
				rcftRxUnderSizePackets      Counter32,
				rcftRxOverSizePackets        Counter32,
				rcftRxPausePackets      Counter32,
				rcftRxOamPackets        Counter32,
				rcftRxBytes             Counter32,
				rcftTxPackets           Counter32,
				rcftTxFCSErrPackets     Counter32,
				rcftTxPausePackets      Counter32,
				rcftTxOamPackets        Counter32,
				rcftTxBytes             Counter32,
				rcftFluxTimer			Counter32

				}

		rcftPortIndex   OBJECT-TYPE
    		SYNTAX	   Integer32
    		MAX-ACCESS read-only
    		STATUS		current
    		DESCRIPTION
    		"
    			索引
    		"
        	::= { rcftSlotStatisticEntry 1 }

        rcftPortType   OBJECT-TYPE
    		SYNTAX	   INTEGER
    		MAX-ACCESS read-only
    		STATUS		current
    		DESCRIPTION
    		"
    			接口类型

    			1：ethfe口
    			2：ethfx口
    			3：e1口

    		"
        	::= { rcftSlotStatisticEntry 2 }

		rcftRxPackets    OBJECT-TYPE
			SYNTAX Counter32
			MAX-ACCESS read-only
			STATUS current
			DESCRIPTION
			"
				接收包数
			"
			::= { rcftSlotStatisticEntry 3 }

		rcftRxLosPackets        OBJECT-TYPE
			SYNTAX Counter32
			MAX-ACCESS read-only
			STATUS current
			DESCRIPTION
			"
				接收丢包数
			"
			::= { rcftSlotStatisticEntry 4 }

		rcftRxPreabErrPackets   OBJECT-TYPE
			SYNTAX Counter32
			MAX-ACCESS read-only
			STATUS current
			DESCRIPTION
			"
				接收前导码错误包数
			"
			::= { rcftSlotStatisticEntry 5 }

		rcftRxFCSErrPackets     OBJECT-TYPE
			SYNTAX Counter32
			MAX-ACCESS read-only
			STATUS current
			DESCRIPTION
			"
				接收FCS错误包数
			"
			::= { rcftSlotStatisticEntry 6 }

		rcftRxUnderSizePackets      OBJECT-TYPE
			SYNTAX Counter32
			MAX-ACCESS read-only
			STATUS current
			DESCRIPTION
			"
				接收超短包数
			"
			::= { rcftSlotStatisticEntry 7 }

		rcftRxOverSizePackets        OBJECT-TYPE
			SYNTAX Counter32
			MAX-ACCESS read-only
			STATUS current
			DESCRIPTION
			"
				接收超长报数
			"
			::= { rcftSlotStatisticEntry 8 }

		rcftRxPausePackets      OBJECT-TYPE
			SYNTAX Counter32
			MAX-ACCESS read-only
			STATUS current
			DESCRIPTION
			"
				接收PAUSE 包数
			"
			::= { rcftSlotStatisticEntry 9 }

		rcftRxOamPackets        OBJECT-TYPE
			SYNTAX Counter32
			MAX-ACCESS read-only
			STATUS current
			DESCRIPTION
			"
				接收OAM包数
			"
			::= { rcftSlotStatisticEntry 10 }

		rcftRxBytes             OBJECT-TYPE
			SYNTAX Counter32
			MAX-ACCESS read-only
			STATUS current
			DESCRIPTION
			"
				接收字节数
			"
			::= { rcftSlotStatisticEntry 11 }

		rcftTxPackets           OBJECT-TYPE
			SYNTAX Counter32
			MAX-ACCESS read-only
			STATUS current
			DESCRIPTION
			"
				发送包数
			"
			::= { rcftSlotStatisticEntry 12 }

		rcftTxFCSErrPackets     OBJECT-TYPE
			SYNTAX Counter32
			MAX-ACCESS read-only
			STATUS current
			DESCRIPTION
			"
				发送FCS错误包数（由GFP解帧模块检测到的）
			"
			::= { rcftSlotStatisticEntry 13 }

		rcftTxPausePackets      OBJECT-TYPE
			SYNTAX Counter32
			MAX-ACCESS read-only
			STATUS current
			DESCRIPTION
			"
				发送PAUSE包数
			"
			::= { rcftSlotStatisticEntry 14 }

		rcftTxOamPackets        OBJECT-TYPE
			SYNTAX Counter32
			MAX-ACCESS read-only
			STATUS current
			DESCRIPTION
			"
				发送OAM包数
			"
			::= { rcftSlotStatisticEntry 15 }

		rcftTxBytes      OBJECT-TYPE
			SYNTAX Counter32
			MAX-ACCESS read-only
			STATUS current
			DESCRIPTION
			"
				发送字节数
			"
			::= { rcftSlotStatisticEntry 16 }

		rcftFluxTimer    OBJECT-TYPE
			SYNTAX Counter32
			MAX-ACCESS read-only
			STATUS current
			DESCRIPTION
			"
				流量统计时间
			"
			::= { rcftSlotStatisticEntry 17 }

  -----------------------VCG MIB----------------------------
     rcftSlotVCGTable OBJECT-TYPE
       SYNTAX  SEQUENCE OF RcftSlotVCGEntry
       MAX-ACCESS  not-accessible
       STATUS  current
       DESCRIPTION
       "
         The VCG table.
       "
       ::= { rcftSlotVCGObjects 1 }

    rcftSlotVCGEntry OBJECT-TYPE
       SYNTAX  RcftSlotVCGEntry
       MAX-ACCESS  not-accessible
       STATUS  current
       DESCRIPTION
       "
          An entry in the VCG table.

       "
       INDEX   { rcftChassisIndex, rcftSlotIndex,rcftSlotVCGIndex }
       ::= { rcftSlotVCGTable 1 }


    RcftSlotVCGEntry ::=
       SEQUENCE {
       rcftSlotVCGIndex		 	Integer32,
       rcftSlotVCGStatus		INTEGER,
       rcftSlotVCGLoopStatus	INTEGER,
       rcftSlotVCGLcasXPR		INTEGER,
       rcftSlotVCGLcasXAR		INTEGER,
       rcftSlotVCGLcasXPT		INTEGER,
       rcftSlotVCGLcasXAT		INTEGER,
       rcftSlotVCGAlarmStatus	INTEGER,
       rcftSlotVCGTxISPTPID     INTEGER,
       rcftSlotVCGRxISPTPID     INTEGER,
       rcftSlotVCGBaseCoS 		INTEGER,
       rcftSlotVCGVLANID		INTEGER,
       rcftSlotVCGMemberList	OCTET STRING,
       rcftSlotToRVCGMemberList	  OCTET STRING,
       rcftSlotVCGMemberStatus    OCTET STRING,
       rcftSlotVCGMemberRxCode    OCTET STRING,
       rcftSlotVCGMemberTxCode    OCTET STRING,
       rcftSlotVCGMemberAlarmStatus  	OCTET STRING,
       rcftSlotToRVCGMemberAlarmStatus  OCTET STRING

       }


    rcftSlotVCGIndex OBJECT-TYPE
    	SYNTAX	   Integer32
    	MAX-ACCESS read-only
    	STATUS		current
    	DESCRIPTION
    	"
    		VCG 的索引
    	"
        ::= { rcftSlotVCGEntry 1 }

        rcftSlotVCGStatus OBJECT-TYPE
        SYNTAX INTEGER
        MAX-ACCESS read-write
        STATUS current
        DESCRIPTION
        "
        	bit10:CSF发送				1：使能，0：禁止
        	bit9：对端VLI。				1：使能，0：禁止
        	bit8：对端Vcat。			1：使能，0：禁止
            bit7：对端Lcas。			1：使能，0：禁止

        	bit6：是否带tag 				1：使能，0：禁止
        	bit5：CheckLoop。				1：使能，0：禁止
        	bit4：Fcs。						1：使能，0：禁止
        	bit3：GFP净荷扰码Scrb。			1：使能，0：禁止
        	bit2：VLI。						1：使能，0：禁止
        	bit1：Vcat。					1：使能，0：禁止
        	bit0：Lcas。					1：使能，0：禁止

        	LCAS on时，VCAT不可配（内部强制使能）。
        	只有LCAS off时，网管可配VCAT。
			VLI始终可配，但是只在LCAS off、VCAT 禁止时配置生效。
        "
        ::= {rcftSlotVCGEntry 2}

        rcftSlotVCGLoopStatus	OBJECT-TYPE
        SYNTAX INTEGER
        MAX-ACCESS read-only
        STATUS current
        DESCRIPTION
        "
           0：无环，1~63：表示有环的VCG号
        "
        ::= {rcftSlotVCGEntry 3}
        rcftSlotVCGLcasXPR  OBJECT-TYPE
        SYNTAX INTEGER
        MAX-ACCESS read-only
        STATUS current
        DESCRIPTION
        "
           	接收配置成员数（1-E1接口数目）
        "
        ::= {rcftSlotVCGEntry 4}

        rcftSlotVCGLcasXAR  OBJECT-TYPE
        SYNTAX INTEGER
        MAX-ACCESS read-only
        STATUS current
        DESCRIPTION
        "
           	接收实际成员数（1-E1接口数目）
        "
        ::= {rcftSlotVCGEntry 5}

        rcftSlotVCGLcasXPT  OBJECT-TYPE
        SYNTAX INTEGER
        MAX-ACCESS read-only
        STATUS current
        DESCRIPTION
        "
           	 发送配置成员数（1-E1接口数目）
        "
        ::= {rcftSlotVCGEntry 6}

        rcftSlotVCGLcasXAT  OBJECT-TYPE
        SYNTAX INTEGER
        MAX-ACCESS read-only
        STATUS current
        DESCRIPTION
        "
           	 发送实际成员数（1-E1接口数目）
        "
        ::= {rcftSlotVCGEntry 7}
        rcftSlotVCGAlarmStatus	OBJECT-TYPE
        SYNTAX INTEGER
        MAX-ACCESS read-only
        STATUS current
        DESCRIPTION
        "
           	 VCG 告警    0：告警，1：正常
           	 bit0：GID
           	 bit1：LOA
			 bit2：LFD
			 bit3：CFS
             bit4：TLCT
           	 bit5：PLCT
           	 bit6：TLCR
			 bit7：PLCR

			 bit8：对端GID：
			 bit9：对端LOA
			 bit10：对端LFD
			 bit11：对端TLCT
		 	 bit12：对端PLCT
			 bit13：对端TLCR
			 bit14：对端PLCR

        "
        ::= {rcftSlotVCGEntry 8}

       rcftSlotVCGTxISPTPID  OBJECT-TYPE
        SYNTAX INTEGER
        MAX-ACCESS read-write
        STATUS current
        DESCRIPTION
       	"
           	发送侧 TPID
       	"
       	::= {rcftSlotVCGEntry 9}

       rcftSlotVCGRxISPTPID  OBJECT-TYPE
        SYNTAX INTEGER
        MAX-ACCESS read-write
        STATUS current
        DESCRIPTION
       	"
           	接收侧 TPID
       	"
       	::= {rcftSlotVCGEntry 10}


       rcftSlotVCGBaseCoS 		OBJECT-TYPE
        SYNTAX INTEGER
        MAX-ACCESS read-write
        STATUS current
        DESCRIPTION
       	"
           	COS：0~7
       	"
       	::= {rcftSlotVCGEntry 11}

       rcftSlotVCGVLANID  OBJECT-TYPE
        SYNTAX INTEGER
        MAX-ACCESS read-write
        STATUS current
        DESCRIPTION
       	"
           	VLANID
       	"
       	::= {rcftSlotVCGEntry 12}

       	rcftSlotVCGMemberList  OBJECT-TYPE
	  		SYNTAX	OCTET STRING(SIZE (0..15))
			MAX-ACCESS	read-write
			STATUS	current
			DESCRIPTION
			"
			  E1成员列表，每个字节表示1个成员对应的E1端口号。
				此节点为字节串，各成员之间有先后顺序，字节串从左到右依次表示1-N个成员。
				每个字节为0表示该成员无效。
			"
            ::={rcftSlotVCGEntry 13}

       rcftSlotToRVCGMemberList	  OBJECT-TYPE
	  		SYNTAX	OCTET STRING(SIZE (0..15))
			MAX-ACCESS	read-write
			STATUS	current
			DESCRIPTION
			"
			  对端E1成员列表，每个字节表示1个成员对应的E1端口号。
				此节点为字节串，各成员之间有先后顺序，字节串从左到右依次表示1-N个成员。
				每个字节为0表示该成员无效。
			"
            ::={rcftSlotVCGEntry 14}

       rcftSlotVCGMemberStatus    OBJECT-TYPE
	  		SYNTAX	OCTET STRING(SIZE (0..15))
			MAX-ACCESS	read-write
			STATUS	current
			DESCRIPTION
			"
			  此节点为字节串，各成员之间有先后顺序，字节串从左到右依次表示1-N个成员。
				每个字节的：
				bit0：接收成员状态。		1：OK，0：Error。
				bit1：发送成员状态。		1：OK，2：Error。
			"
            ::={rcftSlotVCGEntry 15}

       rcftSlotVCGMemberRxCode    OBJECT-TYPE
	  		SYNTAX	OCTET STRING(SIZE (0..15))
			MAX-ACCESS	read-only
			STATUS	current
			DESCRIPTION
			"
			  成员接收控制字，此节点为字节串，各成员之间有先后顺序，字节串从左到右依次表示1-N个成员。
				每个字节的枚举值如下：
					1：FIXED：固定带宽，非LCAS模式。
					2：ADD：将当前成员添加到VCG组中。
					3：NORM：正在添加， 通道良好。
					4：EOS：添加结束。
					5：IDLE：当前成员没有添加到VCG中。
					6：DNU：已添加但是通道故障。

			"
            ::={rcftSlotVCGEntry 16}

       rcftSlotVCGMemberTxCode    OBJECT-TYPE
	  		SYNTAX	OCTET STRING(SIZE (0..15))
			MAX-ACCESS	read-only
			STATUS	current
			DESCRIPTION
			"
			  成员发送控制字，此节点为字节串，各成员之间有先后顺序，字节串从左到右依次表示1-N个成员。
				每个字节的枚举值如下：
					1：FIXED
					2：ADD
					3：NORM
					4：EOS
					5：IDLE
					6：DNU

			"
            ::={rcftSlotVCGEntry 17}

       rcftSlotVCGMemberAlarmStatus  	OBJECT-TYPE
	  		SYNTAX	OCTET STRING(SIZE (0..15))
			MAX-ACCESS	read-only
			STATUS	current
			DESCRIPTION
			"
			  成员告警状态，此节点为字节串，各成员之间有先后顺序，字节串从左到右依次表示1-N个成员。
				每个字节的bit位定义如下：
					Bit0：LOM：复帧失步告警
					Bit1：CRC：
					Bit2：SQM：序列指示失配告警
					Bit3：LOA：成员定位丢失

			"
            ::={rcftSlotVCGEntry 18}

       rcftSlotToRVCGMemberAlarmStatus  OBJECT-TYPE
	  		SYNTAX	OCTET STRING(SIZE (0..15))
			MAX-ACCESS	read-only
			STATUS	current
			DESCRIPTION
			"
			  对端成员告警状态，此节点为字节串，各成员之间有先后顺序，字节串从左到右依次表示1-N个成员。
				每个字节的bit位定义如下：
					Bit0：对端LOM
					Bit1：对端CRC
					Bit2：对端SQM
					Bit3：对端LOA
			"
            ::={rcftSlotVCGEntry 19}



         --------------------------VCG GFP帧流量统计--------------------------
         rcftSlotVCGStatisticTable OBJECT-TYPE
	        SYNTAX SEQUENCE OF RcftSlotVCGStatisticEntry
	        MAX-ACCESS not-accessible
	        STATUS current
	        DESCRIPTION
	          "
	          局端设备GFP的统计表.
	          "
            ::= {rcftSlotVCGPerformance 1}
	    rcftSlotVCGStatisticEntry OBJECT-TYPE
	        SYNTAX RcftSlotVCGStatisticEntry
	        MAX-ACCESS not-accessible
	        STATUS current
	        DESCRIPTION
	          "
	             以rcftSlotVCGIndex为索引
	          "
	        AUGMENTS { rcftSlotVCGEntry }
	        ::= {rcftSlotVCGStatisticTable 1}
	    RcftSlotVCGStatisticEntry ::= SEQUENCE {
				rcftVCGRxClientPackets    	  Counter32,
				rcftVCGRxIdlePackets		   Counter32,
				rcftVCGRxMgmntPackets		  Counter32,
				rcftVCGRxFCSErrMgmntPackets   Counter32,
				rcftVCGRxLenErrPackets   	  Counter32,
				rcftVCGRxFCSErrClientPackets  Counter32,
				rcftVCGRxThecErrPackets     Counter32,
				rcftVCGRxEhecErrPackets     Counter32,
				rcftVCGRxCIDErrPackets      Counter32,
				rcftVCGRxSpareErrPackets    Counter32,
				rcftVCGRxChecCorPackets     Counter32,
				rcftVCGRxThecCorPackets     Counter32,
				rcftVCGRxEhecCorPackets     Counter32,
				rcftVCGRxBytes          	Counter32,
				rcftVCGTxClientPackets        Counter32,
				rcftVCGTxIdlePackets        Counter32,
				rcftVCGTxMgmntPackets		Counter32,
				rcftVCGTxBytes				Counter32,
				rcftVCGFluxTimer		    Counter32
	         }

          rcftVCGRxClientPackets    OBJECT-TYPE
				SYNTAX Counter32
				MAX-ACCESS read-only
				STATUS current
				DESCRIPTION
				"
					接收客户数据包数
				"
				::= { rcftSlotVCGStatisticEntry 1 }

				rcftVCGRxIdlePackets   OBJECT-TYPE
				SYNTAX Counter32
				MAX-ACCESS read-only
				STATUS current
				DESCRIPTION
				"
					接收空闲数据包数
				"
				::= { rcftSlotVCGStatisticEntry 2 }

				rcftVCGRxMgmntPackets	OBJECT-TYPE
				SYNTAX Counter32
				MAX-ACCESS read-only
				STATUS current
				DESCRIPTION
				"
					接收网管数据包数
				"
				::= { rcftSlotVCGStatisticEntry 3 }

				rcftVCGRxFCSErrMgmntPackets  OBJECT-TYPE
				SYNTAX Counter32
				MAX-ACCESS read-only
				STATUS current
				DESCRIPTION
				"
					 接收FCS错误包数
				"
				::= { rcftSlotVCGStatisticEntry 4 }

				rcftVCGRxLenErrPackets   	OBJECT-TYPE
				SYNTAX Counter32
				MAX-ACCESS read-only
				STATUS current
				DESCRIPTION
				"
					 接收长度错误包数
				"
				::= { rcftSlotVCGStatisticEntry 5 }

				rcftVCGRxFCSErrClientPackets  OBJECT-TYPE
				SYNTAX Counter32
				MAX-ACCESS read-only
				STATUS current
				DESCRIPTION
				"
					  接收FCS错误客户数据包数
				"
				::= { rcftSlotVCGStatisticEntry 6 }

				rcftVCGRxThecErrPackets     OBJECT-TYPE
				SYNTAX Counter32
				MAX-ACCESS read-only
				STATUS current
				DESCRIPTION
				"
					 接收类型域错误包数
				"
				::= { rcftSlotVCGStatisticEntry 7 }

				rcftVCGRxEhecErrPackets     OBJECT-TYPE
				SYNTAX Counter32
				MAX-ACCESS read-only
				STATUS current
				DESCRIPTION
				"
					 接收扩展类型域错误包数
				"
				::= { rcftSlotVCGStatisticEntry 8 }

				rcftVCGRxCIDErrPackets      OBJECT-TYPE
				SYNTAX Counter32
				MAX-ACCESS read-only
				STATUS current
				DESCRIPTION
				"
					  	接收客户数据帧扩展域CID与期望值不同错误包数
				"
				::= { rcftSlotVCGStatisticEntry 9 }

				rcftVCGRxSpareErrPackets    OBJECT-TYPE
				SYNTAX Counter32
				MAX-ACCESS read-only
				STATUS current
				DESCRIPTION
				"
					 	接收客户数据帧扩展域Spare与期望值不同错误包数
				"
				::= { rcftSlotVCGStatisticEntry 10 }

				rcftVCGRxChecCorPackets     OBJECT-TYPE
				SYNTAX Counter32
				MAX-ACCESS read-only
				STATUS current
				DESCRIPTION
				"
					 	接收帧头纠错包数
				"
				::= { rcftSlotVCGStatisticEntry 11 }

				rcftVCGRxThecCorPackets     OBJECT-TYPE
				SYNTAX Counter32
				MAX-ACCESS read-only
				STATUS current
				DESCRIPTION
				"
					  	接收类型域纠错包数
				"
				::= { rcftSlotVCGStatisticEntry 12 }

				rcftVCGRxEhecCorPackets     OBJECT-TYPE
				SYNTAX Counter32
				MAX-ACCESS read-only
				STATUS current
				DESCRIPTION
				"
					  	接收扩展域纠错包数
				"
				::= { rcftSlotVCGStatisticEntry 13 }

				rcftVCGRxBytes          OBJECT-TYPE
				SYNTAX Counter32
				MAX-ACCESS read-only
				STATUS current
				DESCRIPTION
				"
					  	接收字节数
				"
				::= { rcftSlotVCGStatisticEntry 14 }

				rcftVCGTxClientPackets        OBJECT-TYPE
				SYNTAX Counter32
				MAX-ACCESS read-only
				STATUS current
				DESCRIPTION
				"
					 	发送客户包数
				"
				::= { rcftSlotVCGStatisticEntry 15 }

				rcftVCGTxIdlePackets        OBJECT-TYPE
				SYNTAX Counter32
				MAX-ACCESS read-only
				STATUS current
				DESCRIPTION
				"
					 	发送空闲包数
				"
				::= { rcftSlotVCGStatisticEntry 16 }

				rcftVCGTxMgmntPackets    OBJECT-TYPE
				SYNTAX Counter32
				MAX-ACCESS read-only
				STATUS current
				DESCRIPTION
				"
					 	发送字节数
				"
				::= { rcftSlotVCGStatisticEntry 17 }


				rcftVCGTxBytes				OBJECT-TYPE
				SYNTAX Counter32
				MAX-ACCESS read-only
				STATUS current
				DESCRIPTION
				"
					 	发送字节数
				"
				::= { rcftSlotVCGStatisticEntry 18 }

    	        rcftVCGFluxTimer		   OBJECT-TYPE
				SYNTAX Counter32
				MAX-ACCESS read-only
				STATUS current
				DESCRIPTION
				"
					 流量统计时间
				"
				::= { rcftSlotVCGStatisticEntry 19 }


     --------------------------VCG 的告警------------------------

       rcftSlotVCGGIDTraps 	NOTIFICATION-TYPE
      	OBJECTS{
			rcftSlotVCGAlarmStatus
      	}
      	STATUS current
     	DESCRIPTION
     	"
     		VCG成员的 的VCG-ID 错误 GID告警
     	"
     	::= { rcftSlotVCGTraps 1 }

     	rcftSlotVCGLOATraps 	NOTIFICATION-TYPE
      	OBJECTS{
			rcftSlotVCGAlarmStatus
      	}
      	STATUS current
     	DESCRIPTION
     	"
     		VCG成员的 的LOA告警
     		LOA：VCAT使能时，成员相对延时差超过设定范围告警的或。
     	"
     	::= { rcftSlotVCGTraps 2 }

     	rcftSlotVCGLFDTraps 	NOTIFICATION-TYPE
      	OBJECTS{
			rcftSlotVCGAlarmStatus
      	}
      	STATUS current
     	DESCRIPTION
     	"
     		VCG成员的 的LFD告警
     		LFD：GFP帧定界告警
     	"
     	::= { rcftSlotVCGTraps 3 }
       rcftSlotVCGCSFTraps 	NOTIFICATION-TYPE
      	OBJECTS{
			rcftSlotVCGAlarmStatus
      	}
      	STATUS current
     	DESCRIPTION
     	"
     		VCG成员的 的CSF告警
     		CSF：GFP客户信号失效告警
     	"
     	::= { rcftSlotVCGTraps 4 }

     	rcftSlotVCGTLCTTraps   NOTIFICATION-TYPE
      	OBJECTS{
			rcftSlotVCGAlarmStatus
      	}
      	STATUS current
     	DESCRIPTION
     	"
     		LCAS发送侧全部成员失效告警
      	"
     	::= { rcftSlotVCGTraps 5 }

     	rcftSlotVCGTLCRTraps     NOTIFICATION-TYPE
      	OBJECTS{
			rcftSlotVCGAlarmStatus
      	}
      	STATUS current
     	DESCRIPTION
     	"
     		LCAS接收侧全部成员失效告警

     	"
     	::= { rcftSlotVCGTraps 6 }

    	rcftSlotVCGToRGIDTraps 	NOTIFICATION-TYPE
      	OBJECTS{
			rcftSlotVCGAlarmStatus
      	}
      	STATUS current
     	DESCRIPTION
     	"
     		VCG成员的 的VCG-ID 错误 GID告警
     	"
     	::= { rcftSlotVCGTraps 7 }

     	rcftSlotVCGToRLOATraps 	NOTIFICATION-TYPE
      	OBJECTS{
			rcftSlotVCGAlarmStatus
      	}
      	STATUS current
     	DESCRIPTION
     	"
     		VCG成员的 的LOA告警
     		LOA：VCAT使能时，成员相对延时差超过设定范围告警的或。
     	"
     	::= { rcftSlotVCGTraps 8 }

     	rcftSlotVCGToRLFDTraps 	NOTIFICATION-TYPE
      	OBJECTS{
			rcftSlotVCGAlarmStatus
      	}
      	STATUS current
     	DESCRIPTION
     	"
     		VCG成员的 的LFD告警
     		LFD：GFP帧定界告警
     	"
     	::= { rcftSlotVCGTraps 9 }


       rcftSlotVCGMemberLOMTraps 	NOTIFICATION-TYPE
      	OBJECTS{
			rcftSlotVCGMemberAlarmStatus
      	}
      	STATUS current
     	DESCRIPTION
     	"
     		VCG成员的 的复帧失步LOM 告警
     	"
     	::= { rcftSlotVCGTraps 10 }

     	rcftSlotVCGMemberSQMTraps 	NOTIFICATION-TYPE
      	OBJECTS{
			rcftSlotVCGMemberAlarmStatus
      	}
      	STATUS current
     	DESCRIPTION
     	"
     		VCG成员的 的SQM告警
     		SQM ：VCAT使能时，成员的SQ值不符告警。
     	"
     	::= { rcftSlotVCGTraps 11 }

     	rcftSlotVCGMemberCRCTraps 	NOTIFICATION-TYPE
      	OBJECTS{
			rcftSlotVCGMemberAlarmStatus
      	}
      	STATUS current
     	DESCRIPTION
     	"
     		VCG成员的 的CRC告警
       	"
     	::= { rcftSlotVCGTraps 12 }

     	rcftSlotVCGMemberLOATraps 	NOTIFICATION-TYPE
      	OBJECTS{
			rcftSlotToRVCGMemberAlarmStatus
      	}
      	STATUS current
     	DESCRIPTION
     	"
     		VCG成员的 的LOA告警
     		LOA：成员的相对延时差超过设定范围告警

       	"
     	::= { rcftSlotVCGTraps 13 }


      rcftSlotVCGToRMemberLOMTraps 	NOTIFICATION-TYPE
      	OBJECTS{
			rcftSlotToRVCGMemberAlarmStatus
      	}
      	STATUS current
     	DESCRIPTION
     	"
     		VCG成员的 的复帧失步LOM 告警
     	"
     	::= { rcftSlotVCGTraps 14 }

     	rcftSlotVCGToRMemberSQMTraps 	NOTIFICATION-TYPE
      	OBJECTS{
			rcftSlotToRVCGMemberAlarmStatus
      	}
      	STATUS current
     	DESCRIPTION
     	"
     		VCG成员的 的SQM告警
     		SQM ：VCAT使能时，成员的SQ值不符告警。
     	"
     	::= { rcftSlotVCGTraps 15 }

     	rcftSlotVCGToRMemberCRCTraps 	NOTIFICATION-TYPE
      	OBJECTS{
			rcftSlotToRVCGMemberAlarmStatus
      	}
      	STATUS current
     	DESCRIPTION
     	"
     		VCG成员的 的CRC告警
       	"
     	::= { rcftSlotVCGTraps 16 }

     	rcftSlotVCGToRMemberLOATraps 	NOTIFICATION-TYPE
      	OBJECTS{
			rcftSlotToRVCGMemberAlarmStatus
      	}
      	STATUS current
     	DESCRIPTION
     	"
     		VCG成员的 的LOA告警
     		LOA：成员的相对延时差超过设定范围告警

       	"
     	::= { rcftSlotVCGTraps 17 }




    -----------------------VLAN MIB----------------------------
     rcftSlotVLANTable OBJECT-TYPE
       SYNTAX  SEQUENCE OF RcftSlotVLANEntry
       MAX-ACCESS  not-accessible
       STATUS  current
       DESCRIPTION
       "
         The VLAN table.
       "
       ::= { rcftSlotVLANObjects 1 }

    rcftSlotVLANEntry OBJECT-TYPE
       SYNTAX  RcftSlotVLANEntry
       MAX-ACCESS  not-accessible
       STATUS  current
       DESCRIPTION
       "
          An entry in the VLAN table.

       "
       INDEX   { rcftChassisIndex, rcftSlotIndex,rcftSlotVLANIndex }
       ::= { rcftSlotVLANTable 1 }


    RcftSlotVLANEntry ::=
       SEQUENCE {
       rcftSlotVLANIndex		 	Integer32,
       rcftSlotVLANStatus		INTEGER,
       rcftSlotVLANmember		INTEGER,
       rcftSlotVID              INTEGER
       }


    rcftSlotVLANIndex OBJECT-TYPE
    	SYNTAX	   Integer32
    	MAX-ACCESS read-only
    	STATUS		current
    	DESCRIPTION
    	"
    		VLAN 的索引
    	"
        ::= { rcftSlotVLANEntry 1 }

        rcftSlotVLANStatus OBJECT-TYPE
        SYNTAX     INTEGER
        MAX-ACCESS read-write
        STATUS current
        DESCRIPTION
        "
        	1:激活，2：挂起
        "
        ::= {rcftSlotVLANEntry 2}

        rcftSlotVLANmember  OBJECT-TYPE
    	SYNTAX	   INTEGER
    	MAX-ACCESS read-write
    	STATUS		current
    	DESCRIPTION
    	"
    		VLAN表项的端口列表。
			bit31~0对应第32路~~第1路EthFe口，第n位为1表示第n+1端口为该VLAN成员。
    		例如：bit3=1，bit0=1，表示端口4和端口1为该VLAN的成员。
    	"
        ::= { rcftSlotVLANEntry 3 }

      	rcftSlotVID  OBJECT-TYPE
    	SYNTAX	   INTEGER
    	MAX-ACCESS read-write
    	STATUS		current
    	DESCRIPTION
    	"
    		VLANID，范围1~4094。
    	"
        ::= { rcftSlotVLANEntry 4 }

END
