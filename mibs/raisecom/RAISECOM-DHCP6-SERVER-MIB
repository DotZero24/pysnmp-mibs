--MibName=raisecomDhcp6Server
RAISECOM-DHCP6-SERVER-MIB DEFINITIONS ::= BEGIN

    IMPORTS
        MODULE-IDENTITY, TimeTicks, OBJECT-TYPE
             FROM SNMPv2-SMI
        RowStatus,MacAddress FROM SNMPv2-TC
        EnableVar,Vlanset	 FROM SWITCH-TC
        InetAddressIPv6      FROM INET-ADDRESS-MIB
        raisecomAgent        FROM RAISECOM-BASE-MIB;

    raisecomDhcp MODULE-IDENTITY
        LAST-UPDATED "201102180000Z"
        ORGANIZATION "raisecom Group"
        CONTACT-INFO
                "       Raise Systems

                Postal: Beijing,
                        China

                   Tel: 86-010-82884499

                E-mail: aiyingjie@raisecom.com"
        DESCRIPTION
            "The MIB module for DHCPv6 Server Module."
    ::= { raisecomAgent 44}

    raisecomDhcpServer             OBJECT IDENTIFIER ::= { raisecomDhcp 1 }
    raisecomDhcp6Server            OBJECT IDENTIFIER ::= { raisecomDhcpServer 1 }

    raisecomDhcp6SNotifications    OBJECT IDENTIFIER ::= { raisecomDhcp6Server 1 }
    raisecomDhcp6SObjects          OBJECT IDENTIFIER ::= { raisecomDhcp6Server 2 }
    raisecomDhcp6SConformance      OBJECT IDENTIFIER ::= { raisecomDhcp6Server 3 }

    raisecomDhcp6SScalar              OBJECT IDENTIFIER ::= { raisecomDhcp6SObjects 1 }

-----------------raisecomDhcp6ServerConfig-------------------
          raisecomDhcp6SEnable OBJECT-TYPE
              SYNTAX  EnableVar
              MAX-ACCESS  read-write
              STATUS  current
              DESCRIPTION
                      "The global switch of Dhcp6 server."
              DEFVAL { 2 }
              ::= { raisecomDhcp6SScalar 1 }

          raisecomDhcp6SDuid OBJECT-TYPE
              SYNTAX  OCTET STRING (SIZE (0..16))
              MAX-ACCESS  read-only
              STATUS  current
              DESCRIPTION
                      "Indicates the DUID of Server."
              ::= { raisecomDhcp6SScalar 2 }

          raisecomDhcp6SPoolTableNextIndex OBJECT-TYPE
              SYNTAX  INTEGER
              MAX-ACCESS  read-only
              STATUS  current
              DESCRIPTION
                      "The next index of ip address pool."
              DEFVAL { 0 }
              ::= { raisecomDhcp6SObjects 2 }

---------------POOL Table--------------------------
          raisecomDhcp6SPoolTable OBJECT-TYPE
              SYNTAX  SEQUENCE OF raisecomDhcp6SPoolEntry
              MAX-ACCESS  not-accessible
              STATUS  current
              DESCRIPTION
                      "A table that contains DHCP Server State information for ip pool."
              ::= { raisecomDhcp6SObjects 3 }

          raisecomDhcp6SPoolEntry OBJECT-TYPE
              SYNTAX  raisecomDhcp6SPoolEntry
              MAX-ACCESS  not-accessible
              STATUS  current
              DESCRIPTION
                      "An entry that contains DHCP Server State information for ip pool."
              INDEX   { raisecomDhcp6SPoolIndex }
              ::= { raisecomDhcp6SPoolTable 1 }

          raisecomDhcp6SPoolEntry ::=
              SEQUENCE {
                  raisecomDhcp6SPoolIndex INTEGER,
                  raisecomDhcp6SPoolName OCTET STRING,
                  raisecomDhcp6SPoolPrefix InetAddressIPv6,
                  raisecomDhcp6SPoolPrefixLength INTEGER,
                  raisecomDhcp6SPoolPreferredTime INTEGER,
                  raisecomDhcp6SPoolValidTime INTEGER,
                  raisecomDhcp6SPoolDns InetAddressIPv6,
                  raisecomDhcp6SPoolIpInterface INTEGER,
                  raisecomDhcp6SPoolRowStatus INTEGER
                  }

          raisecomDhcp6SPoolIndex OBJECT-TYPE
              SYNTAX  INTEGER
              MAX-ACCESS  not-accessible
              STATUS  current
              DESCRIPTION
                      "The index of ip address pool."
              ::= { raisecomDhcp6SPoolEntry 1 }

          raisecomDhcp6SPoolName OBJECT-TYPE
              SYNTAX  OCTET STRING (SIZE (0..16))
              MAX-ACCESS  read-create
              STATUS  current
              DESCRIPTION
                      "The name of ip address pool."
              ::= { raisecomDhcp6SPoolEntry 2 }

          raisecomDhcp6SPoolPrefix OBJECT-TYPE
              SYNTAX  InetAddressIPv6
              MAX-ACCESS  read-create
              STATUS  current
              DESCRIPTION
                      "The prefix of ip address pool."
              ::= { raisecomDhcp6SPoolEntry 3 }

          raisecomDhcp6SPoolPrefixLength OBJECT-TYPE
              SYNTAX  INTEGER (1..64)
              MAX-ACCESS  read-create
              STATUS  current
              DESCRIPTION
                      "The length of prefix."
              ::= { raisecomDhcp6SPoolEntry 4 }

          raisecomDhcp6SPoolPreferredTime OBJECT-TYPE
              SYNTAX  INTEGER (30..10080 | 4294967295)
              MAX-ACCESS  read-create
              STATUS  current
              DESCRIPTION
                      "The life-time of preferred time.unit is minute."
              DEFVAL {30}
              ::= { raisecomDhcp6SPoolEntry 5 }

          raisecomDhcp6SPoolValidTime OBJECT-TYPE
              SYNTAX  INTEGER (30..10080 | 4294967295)
              MAX-ACCESS  read-create
              STATUS  current
              DESCRIPTION
                      "The life-time of valid time.unit is minute."
              DEFVAL {10080}
              ::= { raisecomDhcp6SPoolEntry 6 }

           raisecomDhcp6SPoolDns OBJECT-TYPE
              SYNTAX  InetAddressIPv6
              MAX-ACCESS  read-create
              STATUS  current
              DESCRIPTION
                      "The ip address of DNS server."
              ::= { raisecomDhcp6SPoolEntry 7 }

          raisecomDhcp6SPoolIpInterface OBJECT-TYPE
              SYNTAX  INTEGER
              MAX-ACCESS  read-create
              STATUS  current
              DESCRIPTION
                      "The ip interface witch the pool applied."
              ::= { raisecomDhcp6SPoolEntry 8 }

          raisecomDhcp6SPoolRowStatus OBJECT-TYPE
              SYNTAX  RowStatus
              MAX-ACCESS  read-create
              STATUS  current
              DESCRIPTION
                      "The row status of this entry.."
              ::= { raisecomDhcp6SPoolEntry 9 }

---------------If Table--------------------------
          raisecomDhcp6SIfTable OBJECT-TYPE
              SYNTAX  SEQUENCE OF raisecomDhcp6SIfEntry
              MAX-ACCESS  not-accessible
              STATUS  current
              DESCRIPTION
                      "A table that contains ip interface information
                      for the DHCP Server."
              ::= { raisecomDhcp6SObjects 4 }

          raisecomDhcp6SIfEntry OBJECT-TYPE
              SYNTAX  raisecomDhcp6SIfEntry
              MAX-ACCESS  not-accessible
              STATUS  current
              DESCRIPTION
                      "An entry that contains ip interface information
                      for the DHCP Server."
              INDEX   { raisecomDhcp6SIfIndex }
              ::= { raisecomDhcp6SIfTable 1 }

          raisecomDhcp6SIfEntry ::=
              SEQUENCE {
                  raisecomDhcp6SIfIndex	   INTEGER,
                  raisecomDhcp6SIfEnable   EnableVar,
                  raisecomDhcp6SIfRapidCommit EnableVar
                  }

          raisecomDhcp6SIfIndex OBJECT-TYPE
              SYNTAX  INTEGER
              MAX-ACCESS  not-accessible
              STATUS  current
              DESCRIPTION
                      "The index of ip interface number."
              ::= { raisecomDhcp6SIfEntry 1 }

          raisecomDhcp6SIfEnable OBJECT-TYPE
              SYNTAX  EnableVar
              MAX-ACCESS  read-write
              STATUS  current
              DESCRIPTION
                      "Enable Dhcp6 Server on interface."
              DEFVAL { 2 }
              ::= { raisecomDhcp6SIfEntry 2 }

          raisecomDhcp6SIfRapidCommit OBJECT-TYPE
              SYNTAX  EnableVar
              MAX-ACCESS  read-write
              STATUS  current
              DESCRIPTION
                      "Indicates whether the rapid commit function is on."
              DEFVAL { 2 }
              ::= { raisecomDhcp6SIfEntry 3 }


---------------dhcp bind table--------------------------
          raisecomDhcp6SBindTable OBJECT-TYPE
              SYNTAX  SEQUENCE OF raisecomDhcp6SBindEntry
              MAX-ACCESS  not-accessible
              STATUS  current
              DESCRIPTION
                      "A table that contains clients binding information."
              ::= { raisecomDhcp6SObjects 5 }

          raisecomDhcp6SBindEntry OBJECT-TYPE
              SYNTAX  raisecomDhcp6SBindEntry
              MAX-ACCESS  not-accessible
              STATUS  current
              DESCRIPTION
                      "A entry that contains clients binding information."
              INDEX   { raisecomDhcp6SBindClientLinkIp }
              ::= { raisecomDhcp6SBindTable 1 }

          raisecomDhcp6SBindEntry ::=
              SEQUENCE {
                  raisecomDhcp6SBindClientLinkIp InetAddressIPv6,
                  raisecomDhcp6SBindClientDuid OCTET STRING,
                  raisecomDhcp6SBindClientIp InetAddressIPv6,
                  raisecomDhcp6SBindIpPreferredTime INTEGER,
                  raisecomDhcp6SBindIpValidTime INTEGER,
                  raisecomDhcp6SBindInterface INTEGER
                  }

          raisecomDhcp6SBindClientLinkIp OBJECT-TYPE
              SYNTAX  InetAddressIPv6
              MAX-ACCESS  not-accessible
              STATUS  current
              DESCRIPTION
                      "The link-local address of client."
              ::= { raisecomDhcp6SBindEntry 1 }

          raisecomDhcp6SBindClientDuid OBJECT-TYPE
              SYNTAX  OCTET STRING (SIZE(0..20))
              MAX-ACCESS   read-only
              STATUS  current
              DESCRIPTION
                      "Indicates the DUID of client."
              ::= { raisecomDhcp6SBindEntry 2 }

          raisecomDhcp6SBindClientIp OBJECT-TYPE
              SYNTAX  InetAddressIPv6
              MAX-ACCESS  read-only
              STATUS  current
              DESCRIPTION
                      "Indicates the IP address of client,
                       witch is assigned by dhcp server."
              ::= { raisecomDhcp6SBindEntry 3 }

          raisecomDhcp6SBindIpPreferredTime OBJECT-TYPE
              SYNTAX    INTEGER
              MAX-ACCESS  read-only
              STATUS  current
              DESCRIPTION
                      "Indicates the preferred time of client ip,
                       witch is assigned by dhcp server."
              ::= { raisecomDhcp6SBindEntry 4 }

           raisecomDhcp6SBindIpValidTime OBJECT-TYPE
              SYNTAX    INTEGER
              MAX-ACCESS  read-only
              STATUS  current
              DESCRIPTION
                      "Indicates the valid  time of client ip,
                       witch is assigned by dhcp server."
              ::= { raisecomDhcp6SBindEntry 5 }

           raisecomDhcp6SBindInterface OBJECT-TYPE
              SYNTAX    INTEGER
              MAX-ACCESS  read-only
              STATUS  current
              DESCRIPTION
                      "Indicates witch ip interface the client attached to."
              ::= { raisecomDhcp6SBindEntry 6 }

 END
