--MibName=raisecomMpls
-- *****************************************************************
-- RAISECOM-MPLS-MIB.mib:  MPLS MIB
--
-- Feb 2009, tangyoucan
--
-- Copyright (c) 1996-2009 by Raisecom Technology Co., Ltd.
-- All rights reserved.
--
-- *****************************************************************
--

  RAISECOM-MPLS-MIB DEFINITIONS ::= BEGIN

  IMPORTS
--     NOTIFICATION-TYPE, MODULE-IDENTITY, OBJECT-TYPE,
--     Integer32, Unsigned32
--        FROM SNMPv2-SMI                     [RFC2578]
ifIndex
        FROM IF-MIB
     --MODULE-COMPLIANCE, OBJECT-GROUP, NOTIFICATION-GROUP
        --FROM SNMPv2-CONF                    [RFC2580]

     TEXTUAL-CONVENTION,TruthValue, RowStatus
        FROM SNMPv2-TC                     -- [RFC2579]
     InterfaceIndexOrZero
        FROM IF-MIB                        -- [RFC2863]

     InetAddressIPv4, InetAddressType, InetAddress
        FROM INET-ADDRESS-MIB              -- [RFC4001]

     pwEntry
        FROM PW-STD-MIB                -- [RFC5601]

     mplsXCEntry
        FROM MPLS-LSR-STD-MIB              -- [RFC3813]

     raisecomAgent
				FROM RAISECOM-BASE-MIB
     ;

  raisecomMpls MODULE-IDENTITY
     LAST-UPDATED "201103120000Z"  -- 12 March 2011 00:00:00 GMT
     ORGANIZATION "Raisecom Technology Co., Ltd."
     CONTACT-INFO
        "Raisecom Science & Technology Co., ltd.
        E-mail: support@raisecom.com ."
     DESCRIPTION
        "This MIB module contains managed object definitions for
         MPLS. "
        ::= { raisecomAgent 25 }

  -- Top-level components of this MIB.
  raisecomMplsLsrObjects OBJECT IDENTIFIER
                                ::= { raisecomMpls 1 }
  raisecomMplsVpnObjects       OBJECT IDENTIFIER
                                ::= { raisecomMpls 2 }
  raisecomMplsLdpObjects       OBJECT IDENTIFIER
                                ::= { raisecomMpls 3 }
  raisecomMplsRsvpTEObjects       OBJECT IDENTIFIER
                                ::= { raisecomMpls 4 }


  RefreshInterval ::= TEXTUAL-CONVENTION
     DISPLAY-HINT "d"
     STATUS   current
     DESCRIPTION
       "The number of milliseconds that  are  expected
       to elapse between refreshes of path or reserva-
       tion state.  Unrefreshed  Path  or  reservation
       state is removed after a small multiple of this
       period."


    SYNTAX   INTEGER (0..'7FFFFFFF'h)

  -- end Top-level components of this MIB

  --Second-level componets of this MIB.
  raisecomMplsL2VpnObjects   OBJECT IDENTIFIER
                        ::= { raisecomMplsVpnObjects 1 }
  -- end Second-level components of this MIB

 --start of config enable information
     raisecomMplsLsrId OBJECT-TYPE
     SYNTAX            InetAddressIPv4
     MAX-ACCESS        read-write
     STATUS            current
     DESCRIPTION
         "MPLS LSR ID."
     ::= { raisecomMplsLsrObjects 1 }

     raisecomMplsEnable OBJECT-TYPE
     SYNTAX            TruthValue
     MAX-ACCESS        read-write
     STATUS            current
     DESCRIPTION
         "MPLS enable."
     DEFVAL { false }
     ::= { raisecomMplsLsrObjects 2 }

     raisecomMplsLspStatisticsClear OBJECT-TYPE
     SYNTAX            TruthValue
     MAX-ACCESS        read-write
     STATUS            current
     DESCRIPTION
         "MPLS LSR Lsp statistics clear."
     DEFVAL { false }
     ::= { raisecomMplsLsrObjects 3 }
--end of config enable information

--start of interface config
  raisecomMplsInterfaceTable   OBJECT-TYPE
     SYNTAX        SEQUENCE OF RaisecomMplsInterfaceEntry
     MAX-ACCESS    not-accessible
     STATUS        current
     DESCRIPTION
         "This table specifies information for configuring the interface mpls information."
     ::= { raisecomMplsLsrObjects 4 }

  raisecomMplsInterfaceEntry   OBJECT-TYPE
     SYNTAX        RaisecomMplsInterfaceEntry
     MAX-ACCESS    not-accessible
     STATUS        current
     DESCRIPTION
          "A row in this table represents the MPLS status information of this interface."
     INDEX  { raisecomMplsInterfaceIndex }
            ::= { raisecomMplsInterfaceTable 1 }

  RaisecomMplsInterfaceEntry ::= SEQUENCE {
        raisecomMplsInterfaceIndex  InterfaceIndexOrZero,
        raisecomMplsInterfaceEnable  TruthValue
       }

  raisecomMplsInterfaceIndex OBJECT-TYPE
     SYNTAX        InterfaceIndexOrZero
     MAX-ACCESS    not-accessible
     STATUS        current
     DESCRIPTION
         "MPLS LSR interface entry interface index."
     ::= { raisecomMplsInterfaceEntry 1 }

  raisecomMplsInterfaceEnable OBJECT-TYPE
     SYNTAX        TruthValue
     MAX-ACCESS    read-write
     STATUS        current
     DESCRIPTION
          "MPLS interface entry mpls enable."
     DEFVAL { true }
     ::= { raisecomMplsInterfaceEntry 2 }
 --end of interface config

 --start of config LSP name
  raisecomMplsLspTable   OBJECT-TYPE
     SYNTAX        SEQUENCE OF RaisecomMplsLspEntry
     MAX-ACCESS    not-accessible
     STATUS        current
     DESCRIPTION
         "This table specifies information for configuring the LSP name."
     ::= { raisecomMplsLsrObjects 5 }

  raisecomMplsLspEntry   OBJECT-TYPE
     SYNTAX        RaisecomMplsLspEntry
     MAX-ACCESS    not-accessible
     STATUS        current
     DESCRIPTION
          "MPLS LSP entry, for manual LSP create. "
     AUGMENTS { mplsXCEntry }
     ::= { raisecomMplsLspTable 1 }

  RaisecomMplsLspEntry ::= SEQUENCE {
        raisecomMplsLspName  OCTET STRING
     }

  raisecomMplsLspName OBJECT-TYPE
     SYNTAX        OCTET STRING (SIZE (0..32))
     MAX-ACCESS    read-write
     STATUS        current
     DESCRIPTION
         "MPLS LSP name. Static lsp identifiered by it."
     ::= { raisecomMplsLspEntry 1 }
--end of LSP name

-- Start of MPSL LSP Statistics.
   raisecomMplsLspStatisticsObjects OBJECT IDENTIFIER
                              ::= { raisecomMplsLsrObjects 6 }

   raisecomMplsLspConfigured OBJECT-TYPE
      SYNTAX        Unsigned32
      MAX-ACCESS    read-only
      STATUS        current
      DESCRIPTION
           "The number of LSPs configured on this device."
      ::= { raisecomMplsLspStatisticsObjects 1 }

   raisecomMplsLspActicve  OBJECT-TYPE
      SYNTAX        Unsigned32
      MAX-ACCESS    read-only
      STATUS        current
      DESCRIPTION
           "The number of active LSPs configured on this device."
      ::= { raisecomMplsLspStatisticsObjects 2 }

   raisecomMplsLspInActicve  OBJECT-TYPE
      SYNTAX        Unsigned32
      MAX-ACCESS    read-only
      STATUS        current
      DESCRIPTION
           "The number of inactive LSPs configured on this device."
      ::= { raisecomMplsLspStatisticsObjects 3 }


   raisecomMplsLspIngress OBJECT-TYPE
      SYNTAX        Unsigned32
      MAX-ACCESS    read-only
      STATUS        current
      DESCRIPTION
           "The number of ingress LSPs configured on this device."
      ::= { raisecomMplsLspStatisticsObjects 4 }

   raisecomMplsLspTransit OBJECT-TYPE
      SYNTAX        Unsigned32
      MAX-ACCESS    read-only
      STATUS        current
      DESCRIPTION
           "The number of transit LSPs configured on this device."
      ::= { raisecomMplsLspStatisticsObjects 5 }

   raisecomMplsLspEgress OBJECT-TYPE
      SYNTAX        Unsigned32
      MAX-ACCESS    read-only
      STATUS        current
      DESCRIPTION
           "The number of tunnels configured on this device. A
             tunnel is considered configured if the
             mplsTunnelRowStatus is active(1)."
      ::= { raisecomMplsLspStatisticsObjects 6 }

   raisecomMplsLspStatic OBJECT-TYPE
      SYNTAX        Unsigned32
      MAX-ACCESS    read-only
      STATUS        current
      DESCRIPTION
           "The number of LSPs configured by SNMP."
      ::= { raisecomMplsLspStatisticsObjects 7 }

   raisecomMplsLspLdp OBJECT-TYPE
      SYNTAX        Unsigned32
      MAX-ACCESS    read-only
      STATUS        current
      DESCRIPTION
           "The number of LSPs configured by LDP."
      ::= { raisecomMplsLspStatisticsObjects 8 }

   raisecomMplsLspRsvpTe OBJECT-TYPE
      SYNTAX        Unsigned32
      MAX-ACCESS    read-only
      STATUS        current
      DESCRIPTION
           "The number of LSPs configured by RSVP-TE."
      ::= { raisecomMplsLspStatisticsObjects 9 }

--end of MPLS LSP Statistics

--start of MPLS TE Notifications

   raisecomMplsTunnelReroutedNotifEnable OBJECT-TYPE
      SYNTAX        TruthValue
      MAX-ACCESS    read-write
      STATUS        current
      DESCRIPTION
           "If this object is true, then it enables the
             generation of mplsTunnelRerouted
             traps, otherwise these traps are not emitted."
      DEFVAL { false }
      ::= { raisecomMplsLsrObjects 7 }

   raisecomMplsTunnelReoptimizedNotifEnable OBJECT-TYPE
      SYNTAX        TruthValue
      MAX-ACCESS    read-write
      STATUS        current
      DESCRIPTION
           "If this object is true, then it enables the
             generation of mplsTunnelReoptimized
             traps, otherwise these traps are not emitted."
      DEFVAL { false }
      ::= { raisecomMplsLsrObjects 8 }

   raisecomMplsTtlPublicPropagate OBJECT-TYPE
      SYNTAX        TruthValue
      MAX-ACCESS    read-write
      STATUS        current
      DESCRIPTION
           "If this object is true, then it enables the
             TTL propagate for public packet."
      DEFVAL { true }
      ::= { raisecomMplsLsrObjects 9 }

   raisecomMplsTtlVpnPropagate OBJECT-TYPE
      SYNTAX        TruthValue
      MAX-ACCESS    read-write
      STATUS        current
      DESCRIPTION
           "If this object is true, then it enables the
             TTL propagate for vpn packet."
      DEFVAL { false }
      ::= { raisecomMplsLsrObjects 10 }

--end of MPLS TE Notifications

 --begin vpn
     raisecomMplsL2vpnEnable OBJECT-TYPE
     SYNTAX            TruthValue
     MAX-ACCESS        read-write
     STATUS            current
     DESCRIPTION
         "MPLS L2VPN enable."
     DEFVAL { false }
     ::= { raisecomMplsL2VpnObjects 1 }

     raisecomMplsL2vpnMartiniEnable OBJECT-TYPE
     SYNTAX            TruthValue
     MAX-ACCESS        read-write
     STATUS            current
     DESCRIPTION
         "MPLS L2VPN martini enable."
     DEFVAL { false }
     ::= { raisecomMplsL2VpnObjects 2 }

  raisecomMplsL2vpnInterfaceTable   OBJECT-TYPE
     SYNTAX        SEQUENCE OF RaisecomMplsL2vpnInterfaceEntry
     MAX-ACCESS    not-accessible
     STATUS        current
     DESCRIPTION
         "This table specifies information for configuring the interface mpls l2 vpn information."
     ::= { raisecomMplsL2VpnObjects  3}

  raisecomMplsL2vpnInterfaceEntry   OBJECT-TYPE
     SYNTAX        RaisecomMplsL2vpnInterfaceEntry
     MAX-ACCESS    not-accessible
     STATUS        current
     DESCRIPTION
          "A row in this table represents the MPLS status information of this interface."
     INDEX  { raisecomMplsL2vpnInterfaceIndex }
            ::= { raisecomMplsL2vpnInterfaceTable 1 }

  RaisecomMplsL2vpnInterfaceEntry ::= SEQUENCE {
        raisecomMplsL2vpnInterfaceIndex       InterfaceIndexOrZero,
        raisecomMplsL2vpnInterfaceEnable      TruthValue
     }

  raisecomMplsL2vpnInterfaceIndex OBJECT-TYPE
     SYNTAX        InterfaceIndexOrZero
     MAX-ACCESS    not-accessible
     STATUS        current
     DESCRIPTION
         "MPLS interface entry interface index."
     ::= { raisecomMplsL2vpnInterfaceEntry 1 }

  raisecomMplsL2vpnInterfaceEnable OBJECT-TYPE
     SYNTAX        TruthValue
     MAX-ACCESS    read-write
     STATUS        current
     DESCRIPTION
         "MPLS interface entry l2vpn enable."
     DEFVAL { true }
     ::= { raisecomMplsL2vpnInterfaceEntry 2 }
  --end of interface config

  --start of ccc pw
   raisecomMplsCccPwTable   OBJECT-TYPE
     SYNTAX           SEQUENCE OF RaisecomMplsCccPwEntry
     MAX-ACCESS       not-accessible
     STATUS           current
     DESCRIPTION
         "This table specifies additional information for ccc PW."
     ::= { raisecomMplsL2VpnObjects 4 }

    raisecomMplsCccPwEntry   OBJECT-TYPE
     SYNTAX        RaisecomMplsCccPwEntry
     MAX-ACCESS    not-accessible
     STATUS        current
     DESCRIPTION
          "ccc PW entry, add next hop information ccc connectiong. "
     AUGMENTS { pwEntry }
     ::= { raisecomMplsCccPwTable 1 }

   RaisecomMplsCccPwEntry ::= SEQUENCE {
        raisecomMplsCccNexthopType  InetAddressType,
        raisecomMplsCccNexthop      InetAddress
     }

     raisecomMplsCccNexthopType OBJECT-TYPE
     SYNTAX            InetAddressType
     MAX-ACCESS        read-create
     STATUS            current
     DESCRIPTION
         "ccc VPN next hop type. it is used only in ccc(pwonly type pw). "
     ::= { raisecomMplsCccPwEntry 1 }

     raisecomMplsCccNexthop OBJECT-TYPE
     SYNTAX            InetAddress
     MAX-ACCESS        read-create
     STATUS            current
     DESCRIPTION
         "ccc VPN next hop address. it is used only in ccc(pwonly type pw). "
     ::= { raisecomMplsCccPwEntry 2 }
 --end of ccc pw
 --end vpn

 --begin ldp
   raisecomMplsLdpEnable OBJECT-TYPE
     SYNTAX            TruthValue
     MAX-ACCESS        read-write
     STATUS            current
     DESCRIPTION
         "MPLS ldp enable."
     DEFVAL { false }
     ::= { raisecomMplsLdpObjects 1 }

   raisecomMplsLdpInterfaceTable   OBJECT-TYPE
     SYNTAX        SEQUENCE OF RaisecomMplsLdpInterfaceEntry
     MAX-ACCESS    not-accessible
     STATUS        current
     DESCRIPTION
         "This table specifies information for configuring the interface mpls information."
     ::= { raisecomMplsLdpObjects 2 }

  raisecomMplsLdpInterfaceEntry   OBJECT-TYPE
     SYNTAX        RaisecomMplsLdpInterfaceEntry
     MAX-ACCESS    not-accessible
     STATUS        current
     DESCRIPTION
          "A row in this table represents the MPLS status information of this interface."
     INDEX  { raisecomMplsLdpInterfaceIndex }

            ::= { raisecomMplsLdpInterfaceTable 1 }

  RaisecomMplsLdpInterfaceEntry ::= SEQUENCE {
        raisecomMplsLdpInterfaceIndex  InterfaceIndexOrZero,
        raisecomMplsLdpInterfaceEnable TruthValue,
        raisecomMplsLdpInterfaceLAM INTEGER,
        raisecomMplsLdpInterfaceTransportAddress InetAddress,
        raisecomMplsLdpInterfaceLdpID OCTET STRING,
        raisecomMplsLdpInterfaceMTU INTEGER,
        raisecomMplsLdpInterfaceKeepAliveHoldTimer INTEGER,
        raisecomMplsLdpInterfaceHelloHoldTimer INTEGER
     }

  raisecomMplsLdpInterfaceIndex OBJECT-TYPE
     SYNTAX        InterfaceIndexOrZero
     MAX-ACCESS    not-accessible
     STATUS        current
     DESCRIPTION
         "MPLS ldp interface entry interface index."
     ::= { raisecomMplsLdpInterfaceEntry 1 }

  raisecomMplsLdpInterfaceEnable OBJECT-TYPE
     SYNTAX        TruthValue
     MAX-ACCESS    read-write
     STATUS        current
     DESCRIPTION
         "MPLS ldp interface entry ldp enable."
     DEFVAL { true }
     ::= { raisecomMplsLdpInterfaceEntry 2 }

  raisecomMplsLdpInterfaceLAM OBJECT-TYPE
     SYNTAX        INTEGER
     MAX-ACCESS    read-only
     STATUS        current
     DESCRIPTION
         "For any given LDP session, the method of label advertisement must be specified."
     ::= { raisecomMplsLdpInterfaceEntry 3 }

  raisecomMplsLdpInterfaceTransportAddress OBJECT-TYPE
     SYNTAX        InetAddress
     MAX-ACCESS    read-only
     STATUS        current
     DESCRIPTION
         "MPLS ldp interface entry ldp enable."
     ::= { raisecomMplsLdpInterfaceEntry 4 }

  raisecomMplsLdpInterfaceLdpID OBJECT-TYPE
     SYNTAX        OCTET STRING
     MAX-ACCESS    read-only
     STATUS        current
     DESCRIPTION
         "The LDP identifier."
     ::= { raisecomMplsLdpInterfaceEntry 5 }

  raisecomMplsLdpInterfaceMTU OBJECT-TYPE
     SYNTAX        INTEGER
     MAX-ACCESS    read-only
     STATUS        current
     DESCRIPTION
         "Maximum transfer units."
     DEFVAL { 1500 }
     ::= { raisecomMplsLdpInterfaceEntry 6 }

  raisecomMplsLdpInterfaceKeepAliveHoldTimer OBJECT-TYPE
     SYNTAX        INTEGER
     MAX-ACCESS    read-write
     STATUS        current
     DESCRIPTION
         "The 16-bit integer value which is the proposed keep alive hold timer for this LDP Entity."
     DEFVAL { 40 }
     ::= { raisecomMplsLdpInterfaceEntry 7 }

  raisecomMplsLdpInterfaceHelloHoldTimer OBJECT-TYPE
     SYNTAX        INTEGER
     MAX-ACCESS    read-write
     STATUS        current
     DESCRIPTION
         "The 16-bit integer value which is the proposed Hello
 	hold timer for this LDP Entity. The Hello Hold time
 	in seconds.

 	An LSR maintains a record of Hellos received
 	from potential peers.  This object represents
 	the Hold Time in the Common Hello Parameters TLV of
 	the Hello Message.

 	A value of 0 is a default value and should be
 	interpretted in conjunction with the
 	mplsLdpEntityTargetPeer object.

 	If the value of this object is 0: if the value of the
 	mplsLdpEntityTargetPeer object is false(2), then this
 	specifies that the Hold Time's actual default value is
 	15 seconds (i.e., the default Hold time for Link Hellos
 	is 15 seconds).  Otherwise if the value of the
 	mplsLdpEntityTargetPeer object is true(1), then this
 	specifies that the Hold Time's actual default value is
 	45 seconds (i.e., the default Hold time for Targeted
 	Hellos is 45 seconds).

 	A value of 65535 means infinite (i.e., wait forever).

 	All other values represent the amount of time in
 	seconds to wait for a Hello Message.  Setting the
 	hold time to a value smaller than 15 is not
 	recommended, although not forbidden according
 	to RFC3036."
     DEFVAL { 0 }
     ::= { raisecomMplsLdpInterfaceEntry 8 }

   raisecomMplsLdpSessionStatusTrapEnable   OBJECT-TYPE
     SYNTAX            TruthValue
     MAX-ACCESS        read-write
     STATUS            current
     DESCRIPTION
         "If this object is true, then it enables the
     generation of mplsLdpSessionUp and mplsLdpSessionDown
     traps, otherwise these traps are not generated."
     DEFVAL { false }
     ::= { raisecomMplsLdpObjects 3 }

   raisecomMplsLdpPathVecLimitTrapEnable   OBJECT-TYPE
     SYNTAX            TruthValue
     MAX-ACCESS        read-write
     STATUS            current
     DESCRIPTION
         "If this object is true, then it enables the
     generation of mplsLdpPathVectorLimitMismatch traps,
     otherwise these traps are not generated."
     DEFVAL { false }
     ::= { raisecomMplsLdpObjects 4 }

   raisecomMplsLdpSessionThreshTrapEnable   OBJECT-TYPE
     SYNTAX            TruthValue
     MAX-ACCESS        read-write
     STATUS            current
     DESCRIPTION
         "If this object is true, then it enables the
     generation of mplsLdpInitSessionThresholdExceeded
     traps, otherwise these traps are not generated."
     DEFVAL { false }
     ::= { raisecomMplsLdpObjects 5 }

--end of interface config
 --end ldp

--begin rsvp-te
   raisecomMplsRsvpTEEnabled OBJECT-TYPE
     SYNTAX            TruthValue
     MAX-ACCESS        read-write
     STATUS            current
     DESCRIPTION
         "MPLS rsvp enable."
     DEFVAL { false }
     ::= { raisecomMplsRsvpTEObjects 1 }

    raisecomMplsRsvpTERefreshInterval OBJECT-TYPE
     SYNTAX            RefreshInterval
     MAX-ACCESS        read-write
     STATUS            current
     DESCRIPTION
         "The interval which is used to set the average
          interval between refresh path and resv messages.

          Note:This is rsvp-te global configuration."
     DEFVAL { 3000  }
     ::= { raisecomMplsRsvpTEObjects 2 }

    raisecomMplsRsvpTERefreshMultiple OBJECT-TYPE
     SYNTAX            INTEGER (1..65536)
     MAX-ACCESS        read-write
     STATUS            current
     DESCRIPTION
         "The RSVP value, K, which is the number of unresponded Path
          or Resv refresh attempts which must be made, spaced by
          the refresh interval before the state is deemed to have.

          Note:This is rsvp-te global configuration."
     DEFVAL { 3  }
     ::= { raisecomMplsRsvpTEObjects 3 }

    raisecomMplsRsvpTERefreshBlockadeMultiple OBJECT-TYPE
     SYNTAX            INTEGER (0..65536)
     MAX-ACCESS        read-write
     STATUS            current
     DESCRIPTION
         "The RSVP value, Kb, which is the number of refresh timeout
          periods after which blockade state is deleted.

          Note:This is rsvp-te global configuration."
     DEFVAL { 0  }
     ::= { raisecomMplsRsvpTEObjects 4 }

    raisecomMplsRsvpTELSPSetupPriority OBJECT-TYPE
     SYNTAX            INTEGER (0..7)
     MAX-ACCESS        read-write
     STATUS            deprecated
     DESCRIPTION
       "The setup priority to apply to LSPs which are not
        signalling this parameter.  0 represents the highest
        priority, 7 the lowest.  The value of this object must be
        numerically more or equal (so lower or equal priority)
        than the value of the holding priority object.

        Note:This is rsvp-te global configuration."
     DEFVAL { 4 }
     ::= { raisecomMplsRsvpTEObjects 5 }

    raisecomMplsRsvpTELSPHoldingPriority OBJECT-TYPE
     SYNTAX            INTEGER (0..7)
     MAX-ACCESS        read-write
     STATUS            deprecated
     DESCRIPTION
      "The holding priority to apply to LSPs which are not
       signalling this parameter.  0 represents the highest
       priority, 7 the lowest.  The value of this object must be
       numerically less or equal (so higher or equal priority)
       than the value of the holding priority object.

       Note:This is rsvp-te global configuration."

     DEFVAL { 3 }
     ::= { raisecomMplsRsvpTEObjects 6 }

    raisecomMplsRsvpTEInitPathRRInterval OBJECT-TYPE
     SYNTAX            INTEGER
     MAX-ACCESS        read-write
     STATUS            current
     DESCRIPTION
      "The rapid retransmission interval in milliseconds before
       an Initial Path message is first resent if no
       acknowledgement is received.
       A Path message is treated as an initial Path if it is the
       Path message which creates the LSP or a Path refresh
       message which requires re-routing.

       Note:This is rsvp-te global configuration."

     DEFVAL { 2000 }
     ::= { raisecomMplsRsvpTEObjects 7 }

    raisecomMplsRsvpTEInitPathRRDecay OBJECT-TYPE
     SYNTAX            INTEGER
     MAX-ACCESS        read-write
     STATUS            current
     DESCRIPTION
       "The percentage increase in the rapid
        retransmission interval for each consecutive
        unacknowledged RSVP Initial Path message.  A value of 0
        indicates a constant retransmission rate.

        A Path message is treated as an initial Path if it is the
        Path message which creates the LSP or a Path refresh
        message which requires re-routing.

        Note:This is rsvp-te global configuration."
     DEFVAL { 100  }
     ::= { raisecomMplsRsvpTEObjects 8 }

    raisecomMplsRsvpTEInitPathRRLimit OBJECT-TYPE
     SYNTAX            INTEGER
     MAX-ACCESS        read-write
     STATUS            current
     DESCRIPTION
       "The maximum number of times an Initial Path message is
        resent if no acknowledgement is received.

        A Path message is treated as an initial Path if it is the
        Path message which creates the LSP or a Path refresh
        message which requires re-routing.

        Note:This is rsvp-te global configuration."
     DEFVAL { 2  }
     ::= { raisecomMplsRsvpTEObjects 9 }

   ------Begin of raisecomMplsRsvpTEInterfaceTable------
   raisecomMplsRsvpTEInterfaceTable   OBJECT-TYPE
     SYNTAX        SEQUENCE OF RaisecomMplsRsvpTEInterfaceEntry
     MAX-ACCESS    not-accessible
     STATUS        current
     DESCRIPTION
         "The RSVP-specific attributes of  the  system's
           interfaces."
     ::= { raisecomMplsRsvpTEObjects 10}

   raisecomMplsRsvpTEInterfaceEntry   OBJECT-TYPE
     SYNTAX        RaisecomMplsRsvpTEInterfaceEntry
     MAX-ACCESS    not-accessible
     STATUS        current
     DESCRIPTION
          "The RSVP-specific attributes of  the  a  given
           interface"
     INDEX  { ifIndex }
            ::= { raisecomMplsRsvpTEInterfaceTable 1 }

   RaisecomMplsRsvpTEInterfaceEntry ::=
   SEQUENCE  {
   raisecomMplsRsvpTEIfRefreshInterval                 RefreshInterval,
   raisecomMplsRsvpTEIfRefreshMultiple                 INTEGER,
   raisecomMplsRsvpTEIfBlockadeMultiple                INTEGER,
   raisecomMplsRsvpTEIfRRInterval                      Unsigned32,
   raisecomMplsRsvpTEIfRRDecay                         Integer32,
   raisecomMplsRsvpTEIfRRLimit                         Unsigned32,
   raisecomMplsRsvpTEIfHelloPeriod                     Unsigned32,
   raisecomMplsRsvpTEIfHelloHoldPeriod                 Unsigned32,
   raisecomMplsRsvpTEIfHelloDecay                      Unsigned32,
   raisecomMplsRsvpTEIfHelloPersist                    Unsigned32,
   raisecomMplsRsvpTEIfEnabled                         TruthValue,
   raisecomMplsRsvpTEIfStatus                          RowStatus
   }

   raisecomMplsRsvpTEIfRefreshInterval OBJECT-TYPE
      SYNTAX      RefreshInterval
      UNITS       "milliseconds"
      MAX-ACCESS  read-write
      STATUS      current
      DESCRIPTION
           "The average interval, in milliseconds, between Path and
            Resv refresh messages for LSPs which use this interface
            for RSVP-TE-signalled data.

            Note:A value of 0 indicates that the globally configured value
            are used on an interface.A value of -1 indicates that Path and
            Resv refresh messages are not required on this interface"
     DEFVAL      { 0 }
       ::= { raisecomMplsRsvpTEInterfaceEntry 1}

    raisecomMplsRsvpTEIfRefreshMultiple OBJECT-TYPE
        SYNTAX      INTEGER (0..65536)
        MAX-ACCESS  read-write
        STATUS      current
        DESCRIPTION
           "The value of the RSVP value 'K', which is  the
            number  of  refresh intervals which must elapse
            (minimum) before a PATH or RESV  message  which
            is not being refreshed will be aged out.

            Note:A value of 0 indicates that the globally
            configuredvalue are used on an interface"
       DEFVAL      { 0 }
       ::= { raisecomMplsRsvpTEInterfaceEntry 2 }

    raisecomMplsRsvpTEIfBlockadeMultiple OBJECT-TYPE
        SYNTAX      INTEGER (0..65536)
        MAX-ACCESS  read-write
        STATUS      current
        DESCRIPTION
           "The value of the RSVP value 'Kb', Which is the
           minimum   number   of  refresh  intervals  that
           blockade state will last once entered.

           Note:A value of 0 indicates that the globally
           are used on an interface"
       DEFVAL      { 0 }
       ::= { raisecomMplsRsvpTEInterfaceEntry 3 }

    raisecomMplsRsvpTEIfRRInterval OBJECT-TYPE
        SYNTAX       Unsigned32
        MAX-ACCESS   read-write
        STATUS       current
        DESCRIPTION
          "Indicates Rapid Retry Interval (in milliseconds) that
           should be used on all interfaces."
        DEFVAL { 500 }
        ::= { raisecomMplsRsvpTEInterfaceEntry 4 }

    raisecomMplsRsvpTEIfRRDecay OBJECT-TYPE
        SYNTAX       Integer32
        MAX-ACCESS   read-write
        STATUS       current
        DESCRIPTION
          "The percentage increase in the rapid retransmission
           interval for each consecutive unacknowledged RSVP message
           sent out of this interface.  A value of 0 indicates a
           constant retransmission rate."
        DEFVAL { 100 }
       ::= { raisecomMplsRsvpTEInterfaceEntry 5 }

    raisecomMplsRsvpTEIfRRLimit OBJECT-TYPE
       SYNTAX       Unsigned32
       MAX-ACCESS   read-write
       STATUS       current
       DESCRIPTION
          "The maximum number of times a message is resent if no
           acknowledgement is received on this interface."
       DEFVAL { 2 }
       ::= { raisecomMplsRsvpTEInterfaceEntry 6 }



    raisecomMplsRsvpTEIfHelloPeriod OBJECT-TYPE
       SYNTAX       Unsigned32
       MAX-ACCESS   read-write
       STATUS       current
       DESCRIPTION
          "Default period in milliseconds between sending Hello
           messages to all neighbors on this interface.  If this is
           set to 0, no Hello messages are sent by this interface.
           Note:This is configured on an interface"
       DEFVAL { 0 }
       ::= { raisecomMplsRsvpTEInterfaceEntry 7 }

    raisecomMplsRsvpTEIfHelloHoldPeriod OBJECT-TYPE
       SYNTAX       Unsigned32
       MAX-ACCESS   read-write
       STATUS       current
       DESCRIPTION
          "Number of hello periods which may pass without receiving a
           successful Hello message from a partner before the Hello
           session times out.
           Note:This is configured on an interface"
       DEFVAL { 3 }
       ::= { raisecomMplsRsvpTEInterfaceEntry 8 }

    raisecomMplsRsvpTEIfHelloDecay OBJECT-TYPE
       SYNTAX       Unsigned32
       MAX-ACCESS   read-write
       STATUS       current
       DESCRIPTION
          "Percentage increase in hello period after each Hello
           message sent when the hello session with the neighbor has
           timed out.
           Note:This is configured on an interface"
       DEFVAL { 0 }
       ::= { raisecomMplsRsvpTEInterfaceEntry 9 }

    raisecomMplsRsvpTEIfHelloPersist OBJECT-TYPE
       SYNTAX       Unsigned32
       MAX-ACCESS   read-write
       STATUS       current
       DESCRIPTION
          "Number of hello periods which may pass after the Hello
           session times out before Hello messages cease.
           Note:This is configured on an interface"
       ::= { raisecomMplsRsvpTEInterfaceEntry 10 }


    raisecomMplsRsvpTEIfEnabled OBJECT-TYPE
      SYNTAX      TruthValue
      MAX-ACCESS  read-write
      STATUS      current
      DESCRIPTION
          "If TRUE, RSVP-TE is enabled  on  this  Interface.
           If  FALSE,  RSVP-TE  is not enabled on this inter-
           face."
      ::= { raisecomMplsRsvpTEInterfaceEntry 11 }

    raisecomMplsRsvpTEIfStatus OBJECT-TYPE
        SYNTAX      RowStatus
        MAX-ACCESS  read-only
        STATUS      current
        DESCRIPTION
           "'active' on interfaces that are configured for
           RSVP."
       ::= { raisecomMplsRsvpTEInterfaceEntry 12 }
  --end   rsvp
  END
