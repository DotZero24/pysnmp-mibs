-- MibName=raisecomAutoProvisionRdev
-- *****************************************************************
-- RAISECOM-AUTOPROVISIONRDEV-MIB.mib:	 Raisecom AUOTPRIVISION MIB file
--
-- Sep 2012, liconge
--
-- Copyright (c) 1994-2012,	2012 by	Raisecom, Inc.
-- All rights reserved.
--
--
-- *****************************************************************

RAISECOM-AUTOPROVISIONRDEV-MIB DEFINITIONS ::= BEGIN

IMPORTS
		    iscomSwitch
				    FROM RAISECOM-BASE-MIB
		    MacAddress
				    FROM SNMPv2-TC
        RowStatus
        		FROM SNMPv2-TC
        Ipv6Address
            FROM IPV6-TC
        PortList
            FROM SWITCH-TC
		    Gauge32
				    FROM SNMPv2-SMI;

raisecomAutoProvisionRdev MODULE-IDENTITY
		LAST-UPDATED	"201209130000Z"
		ORGANIZATION	"Raisecom, Inc."
		CONTACT-INFO
				"		Raise Systems

				    Postal:	Beijing, China

				       Tel:	86-010-82884499

				    E-mail:	support@raisecom.com"
		DESCRIPTION
				"The MIB module for Auto Provision remote device."
				::=	{ iscomSwitch	77 }


-- -------------------------------------------------------------------------- --
--	define groups in RAISECOM-AUOTPRIVISION-MIB
-- -------------------------------------------------------------------------- --
	-- raisecomAutoProvisionMgtTable		      OBJECT IDENTIFIER ::= {	raisecomAutoProvision 1 }
	-- raisecomAutoProvisionRemoteTable		  OBJECT IDENTIFIER ::= {	raisecomAutoProvision 2 }
	-- raisecomAutoProvisionClientInfo	      OBJECT IDENTIFIER ::= {	raisecomAutoProvision 3 }
-- ----------------------------------------------------------------------------

	-- START raisecomAutoProvisionClientInfo

	raisecomAutoProvisionClientInfo	  OBJECT IDENTIFIER ::= {	raisecomAutoProvisionRdev 1 }

	raisecomAutoProvisionClientAdvertiseTerminal   OBJECT-TYPE
		    SYNTAX  INTEGER
		    {
		    	terminal(0),
		    	forward(1)
		    }
		    ACCESS read-write
		    STATUS current
		    DESCRIPTION
		        "The value terminal(0) is used to terminal advertise message, forward(1) is used to forward."
		    ::= {  raisecomAutoProvisionClientInfo 1 }

  raisecomAutoProvisionClientNetworkSegment       OBJECT-TYPE
		    SYNTAX  INTEGER (1..254)
		    ACCESS  read-only
		    STATUS  current
		    DESCRIPTION
		        "Remote device management network segment."
		    ::= {  raisecomAutoProvisionClientInfo 2 }

	raisecomAutoProvisionClientSNMPHost             OBJECT-TYPE
		    SYNTAX  IpAddress
		    ACCESS  read-only
		    STATUS  current
		    DESCRIPTION
		        "SNMP Host IP address of remote device."
		    ::= {  raisecomAutoProvisionClientInfo 3 }

  raisecomAutoProvisionClientSequence             OBJECT-TYPE
		    SYNTAX  INTEGER
		    ACCESS  read-only
		    STATUS  current
		    DESCRIPTION
		        "The sequence ID of Advertise received message."
		    ::= {  raisecomAutoProvisionClientInfo 4 }

  raisecomAutoProvisionClientGenerateARP          OBJECT-TYPE
		    SYNTAX  INTEGER
		    {
     			no(0),
		 			yes(1)
				}
		    ACCESS  read-only
		    STATUS  current
		    DESCRIPTION
		        "This object indicates remote device if generate ARP."
		    ::= {  raisecomAutoProvisionClientInfo 5 }

  raisecomAutoProvisionClientVid                  OBJECT-TYPE
		    SYNTAX  INTEGER (1..4094)
		    ACCESS  read-only
		    STATUS  current
		    DESCRIPTION
		        "VLAN ID the remote device configured."
		    ::= {  raisecomAutoProvisionClientInfo 6 }

	raisecomAutoProvisionClientPort                 OBJECT-TYPE
		    SYNTAX  INTEGER (1..24)
		    ACCESS  read-only
		    STATUS  current
		    DESCRIPTION
		        "The port number the remote device configured."
		    ::= {  raisecomAutoProvisionClientInfo 7 }

  raisecomAutoProvisionClientManageStatus         OBJECT-TYPE
		    SYNTAX  INTEGER
		    		{
              OK(0),
              FAIL(1)
            }
		    ACCESS  read-only
		    STATUS  current
		    DESCRIPTION
		        "The management status of client."
		    ::= {  raisecomAutoProvisionClientInfo 8 }

	raisecomAutoProvisionClientProcAdvertises        OBJECT-TYPE
		    SYNTAX  INTEGER
		    ACCESS  read-only
		    STATUS  current
		    DESCRIPTION
		        "Times of client process Advertises."
		    ::= {  raisecomAutoProvisionClientInfo 9 }

	raisecomAutoProvisionClientDiscardAdvertises        OBJECT-TYPE
		    SYNTAX  INTEGER
		    ACCESS  read-only
		    STATUS  current
		    DESCRIPTION
		        "Times of client discard Advertises."
		    ::= {  raisecomAutoProvisionClientInfo 10 }

	raisecomAutoProvisionClientSendAcks             OBJECT-TYPE
		    SYNTAX  INTEGER
		    ACCESS  read-only
		    STATUS  current
		    DESCRIPTION
		        "Times of client sent Ack."
		    ::= {  raisecomAutoProvisionClientInfo 11 }

  raisecomAutoProvisionClearStatistic             OBJECT-TYPE
		    SYNTAX  INTEGER
		    {
		    	clear(1)
		    }
		    ACCESS  read-write
		    STATUS  current
		    DESCRIPTION
		        "Clear client statistic.."
		    ::= {  raisecomAutoProvisionClientInfo 12 }

	raisecomAutoProvisionClientFuncSwitch                OBJECT-TYPE
		    SYNTAX  INTEGER
		    {
		    	enable(1),
		    	disable(0)
		    }
		    ACCESS  read-write
		    STATUS  current
		    DESCRIPTION
		        "Enable or disable auto-provision client function."
		    ::= {  raisecomAutoProvisionClientInfo 13 }

  raisecomAutoProvisionClientTFTPServer             OBJECT-TYPE
		SYNTAX	IpAddress
		ACCESS	read-only
		STATUS	current
		DESCRIPTION
			"IP address of TFTP server."
		::=	{ raisecomAutoProvisionClientInfo 14 }

	raisecomAutoProvisionClientConfigFileNameRule             OBJECT-TYPE
		SYNTAX	INTEGER (80000..89999)
		ACCESS	read-only
		STATUS	current
		DESCRIPTION
			"The filename rule number."
		::=	{ raisecomAutoProvisionClientInfo 15 }

  raisecomAutoProvisionClientConfigFileNamePrefix             OBJECT-TYPE
		SYNTAX	OCTET STRING (SIZE(0..16))
		ACCESS	read-only
		STATUS	current
		DESCRIPTION
			"The object indicates the config file name prefix."
		::=	{ raisecomAutoProvisionClientInfo 16 }

  raisecomAutoProvisionClientConfigFileNamePostfix             OBJECT-TYPE
		SYNTAX	OCTET STRING (SIZE(0..16))
		ACCESS	read-only
		STATUS	current
		DESCRIPTION
			"IP address of TFTP server."
		::=	{ raisecomAutoProvisionClientInfo 17 }

  -- START raisecomAutoProvisionRcvMsgFromDiffMacTrap

  raisecomAutoProvisionRcvMsgFromDiffDevTrap	  OBJECT IDENTIFIER ::= {	raisecomAutoProvisionRdev 2 }

  raisecomAutoProvisionNewMac            OBJECT-TYPE
		    SYNTAX  MacAddress
		    ACCESS  read-write
		    STATUS  current
		    DESCRIPTION
		        "Device Mac who send new advertise message to the device ."
		    ::= {  raisecomAutoProvisionRcvMsgFromDiffDevTrap 1 }

	raisecomAutoProvisionSavedMac               OBJECT-TYPE
		    SYNTAX  MacAddress
		    ACCESS  read-write
		    STATUS  current
		    DESCRIPTION
		        "Device Mac who have sent advertise message to the device ."
		    ::= {  raisecomAutoProvisionRcvMsgFromDiffDevTrap 2 }

  -- START TRAP raisecomAutoProvisionRdevTrapGroup

  raisecomAutoProvisionRdevTrapGroup	  OBJECT IDENTIFIER ::= {	raisecomAutoProvisionRdev 3 }

  raisecomAutoProvisionLoadCfgFinish          NOTIFICATION-TYPE
        OBJECTS{
            raisecomAutoProvisionClientManageStatus,
            }
        STATUS      current
        DESCRIPTION
        "Loading configuration file finished Trap."
        ::= { raisecomAutoProvisionRdevTrapGroup 1 }

  raisecomAutoProvisionRcvMsgFromDiffDev          NOTIFICATION-TYPE
        OBJECTS{
            raisecomAutoProvisionNewMac,
            raisecomAutoProvisionSavedMac,
            }
        STATUS      current
        DESCRIPTION
        "Receive advertise from other device Trap."
        ::= { raisecomAutoProvisionRdevTrapGroup 2 }

END
