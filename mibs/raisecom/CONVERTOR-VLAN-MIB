--MibName=rcmcVlanConfig
-- =======================================================================
-- Version info
--
-- Version 1.0 Created 2005.07.27 by LONGYAGN
-- This version of MIB is created just for the use of Network Management Systems
-- display and set the system configuration of convertor .
--
-- Copyright(c) 2002-2005 by RAISECOM TECH, Ltd.
-- =======================================================================



CONVERTOR-VLAN-MIB DEFINITIONS ::= BEGIN

	IMPORTS
        MODULE-IDENTITY
                	FROM SNMPv2-SMI
		OBJECT-TYPE
					FROM SNMPv2-SMI
		iscomMediaConvertor
					FROM RAISECOM-BASE-MIB
        PortList,EnableVar
                    FROM SWITCH-TC;

   rcmcVlanConfig MODULE-IDENTITY

        LAST-UPDATED    "200507270000Z"
        ORGANIZATION    "Raisecom Science & Technology Co., ltd"
        CONTACT-INFO    "Raisecom Science & Technology Co., ltd.
                         E-mail: support@raisecom.com"

        DESCRIPTION     "iscom Convertor system Enterprise MIB definition."
        ::= { iscomMediaConvertor 2 }

	rcmcVlanCoreTagType  OBJECT-TYPE
        	SYNTAX  	INTEGER(0..65535)
        	MAX-ACCESS 	read-write
        	STATUS 		current
        	DESCRIPTION
                	"The value of core tag type."
        	DEFVAL  { 37120 }
        	::= { rcmcVlanConfig 1 }

     rcmcVlanSwitchMode	OBJECT-TYPE
         	SYNTAX		INTEGER
         	{
            	transparent(1),
        		dot1q-vlan(2),
        		double-tagged-vlan(3)
         	}
         	MAX-ACCESS  read-write
         	STATUS      current
         	DESCRIPTION
           			"The switch mode of the device is transparent(1) or vlan(2)."
        	::= { rcmcVlanConfig 2 }

     rcmcVlanPortConfigTable  OBJECT-TYPE
			SYNTAX		SEQUENCE OF	RcmcVlanPortConfigEntry
			MAX-ACCESS	not-accessible
			STATUS		current
			DESCRIPTION
				 "A table of ports' vlan information and associated properties."
			::=	{  rcmcVlanConfig 3 }

	rcmcVlanPortConfigEntry  OBJECT-TYPE
			SYNTAX		RcmcVlanPortConfigEntry
			MAX-ACCESS	not-accessible
			STATUS		current
			DESCRIPTION
			   	"Table entry for ports' vlan information."
			INDEX {	rcmcVlanPortIndex }
			::=	{ rcmcVlanPortConfigTable 1 }

	RcmcVlanPortConfigEntry ::= SEQUENCE {
			rcmcVlanPortIndex       			 Integer32,
			rcmcVlanNative     					 INTEGER,
			rcmcVlanNativeOverride    			 EnableVar,
			rcmcVlanDoubleTagEnable      		 EnableVar,
			rcmcVlanIngressFilter				 EnableVar,
			rcmcVlanAcceptFrameType     	   	 INTEGER,
			rcmcVlanEgressDefault      		     INTEGER
			}

     rcmcVlanPortIndex  OBJECT-TYPE
 	      	SYNTAX 	  	Integer32
	      	MAX-ACCESS  not-accessible
	      	STATUS      current
 	      	DESCRIPTION
           			"An index based 1 that uniquely identifies a port entry."
          	::= { rcmcVlanPortConfigEntry 1 }

     rcmcVlanNative  OBJECT-TYPE
        	SYNTAX  	INTEGER(1..4094)
        	MAX-ACCESS 	read-write
        	STATUS 		current
        	DESCRIPTION
                	"Native vlan."
        	::= { rcmcVlanPortConfigEntry 2 }

     rcmcVlanNativeOverride	OBJECT-TYPE
        	SYNTAX  	EnableVar
        	MAX-ACCESS 	read-write
        	STATUS 		current
        	DESCRIPTION
                	"If enable, set all ingress packets' vlan ID
                	 to native vlan. Else, do nothing."
        	DEFVAL  { disable }
        	::= { rcmcVlanPortConfigEntry 3 }

	 rcmcVlanDoubleTagEnable   OBJECT-TYPE
        	SYNTAX  	EnableVar
        	MAX-ACCESS 	read-write
        	STATUS 		current
        	DESCRIPTION
                	"Set double tag to enable(1) or disable(2)."
        	DEFVAL  { disable }
        	::= { rcmcVlanPortConfigEntry 4 }

     rcmcVlanIngressFilter  OBJECT-TYPE
  	        SYNTAX  INTEGER
 	        {
 	        	none(1),
                notmember(2),
                unkown(3)
            }
         	MAX-ACCESS 	read-write
        	STATUS 		current
        	DESCRIPTION
                	"Ingress filter packets type."
         	::= { rcmcVlanPortConfigEntry 5 }

     rcmcVlanAcceptFrameType     OBJECT-TYPE
 	        SYNTAX  INTEGER
 	        {
 	        	all(1),
                tag(2),
                untag(3)
            }
         	MAX-ACCESS 	read-write
        	STATUS 		current
        	DESCRIPTION
                	"Accept frame type."
         	::= { rcmcVlanPortConfigEntry 6 }

	 rcmcVlanEgressDefault   OBJECT-TYPE
        	SYNTAX  INTEGER
        	{
        		unmodify(1),
        	 	tag(2),
            	untag(3),
            	disable(4)
			}
        	MAX-ACCESS 	read-write
        	STATUS 		current
        	DESCRIPTION
            		"The object indicates how to process egress packets
            		if their vlan dosen't exist."
        	DEFVAL  { unmodify }
        	::= { rcmcVlanPortConfigEntry 7 }

END
