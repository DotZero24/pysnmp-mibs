--MibName=raisecomDhcp6Client
RAISECOM-DHCP6-CLIENT-MIB DEFINITIONS ::= BEGIN

    IMPORTS
        MODULE-IDENTITY, TimeTicks, OBJECT-TYPE
             FROM SNMPv2-SMI
        RowStatus,MacAddress FROM SNMPv2-TC
        EnableVar,Vlanset	 FROM SWITCH-TC
        InetAddressIPv6      FROM INET-ADDRESS-MIB
        raisecomAgent        FROM RAISECOM-BASE-MIB;

    raisecomDhcp MODULE-IDENTITY
        LAST-UPDATED "201102180000Z"
        ORGANIZATION "raisecom Group"
        CONTACT-INFO
                "       Raise Systems

                Postal: Beijing,
                        China

                   Tel: 86-010-82884499

                E-mail: wenguan@raisecom.com"
        DESCRIPTION
            "The MIB module for DHCPv6 Client Module."
    ::= { raisecomAgent 44}

    raisecomDhcpClient             OBJECT IDENTIFIER ::= { raisecomDhcp 2 }
    raisecomDhcp6Client            OBJECT IDENTIFIER ::= { raisecomDhcpClient 1 }

    raisecomDhcp6CNotifications    OBJECT IDENTIFIER ::= { raisecomDhcp6Client 1 }
    raisecomDhcp6CObjects          OBJECT IDENTIFIER ::= { raisecomDhcp6Client 2 }
    raisecomDhcp6CConformance      OBJECT IDENTIFIER ::= { raisecomDhcp6Client 3 }

    raisecomDhcp6CScalar              OBJECT IDENTIFIER ::= { raisecomDhcp6CObjects 1 }

-----------------raisecomDhcp6ClientConfig-------------------


          raisecomDhcp6CDuid OBJECT-TYPE
              SYNTAX  OCTET STRING (SIZE (0..128))
              MAX-ACCESS  read-only
              STATUS  current
              DESCRIPTION
                      "Indicates the DUID of Client."
              ::= { raisecomDhcp6CScalar 1 }

---------------dhcp client request table--------------------------
          raisecomDhcp6CRequestTable OBJECT-TYPE
              SYNTAX  SEQUENCE OF raisecomDhcp6CRequestEntry
              MAX-ACCESS  not-accessible
              STATUS  current
              DESCRIPTION
                      "A table that contains client requesting information."
              ::= { raisecomDhcp6CObjects 2 }

          raisecomDhcp6CRequestEntry OBJECT-TYPE
              SYNTAX  raisecomDhcp6CRequestEntry
              MAX-ACCESS  not-accessible
              STATUS  current
              DESCRIPTION
                      "A entry that contains client requesting information."
              INDEX   { raisecomDhcp6CRequestIfIndex }
              ::= { raisecomDhcp6CRequestTable 1 }

          raisecomDhcp6CRequestEntry ::=
              SEQUENCE {
                  raisecomDhcp6CRequestIfIndex INTEGER,
                  raisecomDhcp6CRequestEnable    EnableVar,
                  raisecomDhcp6CRequestRapidCommit  EnableVar,
                  raisecomDhcp6CRequestInformOnly    INTEGER,
                  raisecomDhcp6CRequestOperationStates   INTEGER,
                  raisecomDhcp6CRequestOperationActions   INTEGER,
                  raisecomDhcp6CRequestIpAddress         InetAddressIPv6,
                  raisecomDhcp6CRequestValidTime           INTEGER,
                  raisecomDhcp6CRequestPreferredTime        INTEGER,
                  raisecomDhcp6CRequestTimetoExpire         INTEGER,
                  raisecomDhcp6CRequestDhcpSvr          InetAddressIPv6,
                  raisecomDhcp6CRequestDhcpSvrDuid      OCTET STRING,
                  raisecomDhcp6CRequestSpecifySvr       InetAddressIPv6,
                  raisecomDhcp6CRequestSntpServer       InetAddressIPv6,
                  raisecomDhcp6CRequestDNSServer        InetAddressIPv6
                  }

          raisecomDhcp6CRequestIfIndex OBJECT-TYPE
              SYNTAX  INTEGER
              MAX-ACCESS  not-accessible
              STATUS  current
              DESCRIPTION
                      "The index of if interface of the client."
              ::= { raisecomDhcp6CRequestEntry 1 }

          raisecomDhcp6CRequestEnable OBJECT-TYPE
              SYNTAX  EnableVar
              MAX-ACCESS  read-write
              STATUS  current
              DESCRIPTION
                      "Indicates whether client function is enabled."
              ::= { raisecomDhcp6CRequestEntry 2 }


          raisecomDhcp6CRequestRapidCommit OBJECT-TYPE
              SYNTAX  EnableVar
              MAX-ACCESS  read-write
              STATUS  current
              DESCRIPTION
                      "Indicates whether client rapid commit with the dhcp server."
              ::= { raisecomDhcp6CRequestEntry 3 }


          raisecomDhcp6CRequestInformOnly OBJECT-TYPE
              SYNTAX  INTEGER
              {
              	 false(0),
              	 true(1)
              }
              MAX-ACCESS   read-only
              STATUS  current
              DESCRIPTION
                      "Indicates whether the client request information only without the ip address."
              ::= { raisecomDhcp6CRequestEntry 4 }

          raisecomDhcp6CRequestOperationStates OBJECT-TYPE
              SYNTAX INTEGER
              {
                  solicit(0),
                  bound (1)
              }

              MAX-ACCESS  read-only
              STATUS  current
              DESCRIPTION
                      "Indicates the operation states of dhcp client."
              ::= { raisecomDhcp6CRequestEntry 5 }

          raisecomDhcp6CRequestOperationActions OBJECT-TYPE
                SYNTAX INTEGER
                {
                    idle(0),
                    soliciting(1),
                    requesting(2),
                    renewing(3),
                    rebinding(4),
                    confirming(5),
                    releasing(6)
				}

              MAX-ACCESS  read-write
              STATUS  current
              DESCRIPTION
                      "Indicates the operation actions of dhcp client.Only the renewing(4) can be set successful"
              ::= { raisecomDhcp6CRequestEntry 6 }


          raisecomDhcp6CRequestIpAddress OBJECT-TYPE
              SYNTAX    InetAddressIPv6
              MAX-ACCESS  read-only
              STATUS  current
              DESCRIPTION
                      "Indicates the ip address client get from dhcp server."
              ::= { raisecomDhcp6CRequestEntry 7 }

           raisecomDhcp6CRequestValidTime OBJECT-TYPE
              SYNTAX    INTEGER
              MAX-ACCESS  read-only
              STATUS  current
              DESCRIPTION
                      "Indicates the valid  time of client ip,
                       witch is assigned by dhcp server."
              ::= { raisecomDhcp6CRequestEntry 8 }

            raisecomDhcp6CRequestPreferredTime OBJECT-TYPE
              SYNTAX    INTEGER
              MAX-ACCESS  read-only
              STATUS  current
              DESCRIPTION
                      "Indicates the preferred  time of client ip,
                       witch is assigned by dhcp server."
              ::= { raisecomDhcp6CRequestEntry 9 }

            raisecomDhcp6CRequestTimetoExpire OBJECT-TYPE
              SYNTAX    INTEGER
              MAX-ACCESS  read-only
              STATUS  current
              DESCRIPTION
                      "Indicates the left time of client ip,according to the valid time."
              ::= { raisecomDhcp6CRequestEntry 10 }


          raisecomDhcp6CRequestDhcpSvr OBJECT-TYPE
              SYNTAX    InetAddressIPv6
              MAX-ACCESS  read-only
              STATUS  current
              DESCRIPTION
                      "Indicates the address of dhcp server."
              ::= { raisecomDhcp6CRequestEntry 11 }


          raisecomDhcp6CRequestDhcpSvrDuid OBJECT-TYPE
              SYNTAX  OCTET STRING (SIZE(0..128))
              MAX-ACCESS   read-only
              STATUS  current
              DESCRIPTION
                      "Indicates the DUID of server."
              ::= { raisecomDhcp6CRequestEntry 12 }

          raisecomDhcp6CRequestSpecifySvr OBJECT-TYPE
              SYNTAX    InetAddressIPv6
              MAX-ACCESS  read-write
              STATUS  current
              DESCRIPTION
                      "Indicates the specified address of dhcp server."
              ::= { raisecomDhcp6CRequestEntry 13 }

          raisecomDhcp6CRequestSntpServer OBJECT-TYPE
              SYNTAX    InetAddressIPv6
              MAX-ACCESS  read-only
              STATUS  current
              DESCRIPTION
                      "Indicates the server address of sntp server."
              ::= { raisecomDhcp6CRequestEntry 14 }


          raisecomDhcp6CRequestDNSServer OBJECT-TYPE
              SYNTAX    InetAddressIPv6
              MAX-ACCESS  read-only
              STATUS  current
              DESCRIPTION
                      "Indicates the address of DNS server."
              ::= { raisecomDhcp6CRequestEntry 15 }


 END
