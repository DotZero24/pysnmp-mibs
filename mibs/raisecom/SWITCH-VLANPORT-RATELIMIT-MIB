--MibName=rcRateLimit
-- *****************************************************************
-- RAISECOM-RC3026BANDWIDTHMANAGE-MIB.MIB:  Raisecom Bandwidth Manage MIB file
--
-- May 2003, yuanqingguo
--
-- Copyright (c) 1994-2000, 2001 by Raisecom, Inc.
-- All rights reserved.
--
-- *****************************************************************
SWITCH-VLANPORT-RATELIMIT-MIB  DEFINITIONS ::= BEGIN

IMPORTS
       Counter64
                FROM SNMPv2-SMI
       iscomSwitch
                FROM RAISECOM-BASE-MIB
       RowStatus
                FROM SNMPv2-TC
       EnableVar
                FROM SWITCH-TC;

       rcRateLimit MODULE-IDENTITY
       LAST-UPDATED    "200412200000Z"
       ORGANIZATION    "Raisecom, Inc."
       CONTACT-INFO
                       "Raise Systems

                        Postal: Beijing,
                        China

                        Tel: 86-010-82884499

                        E-mail: yuanqingguo@raisecom.com"
       DESCRIPTION
                       "description of rate limit manage object."
       ::= { iscomSwitch 2}


----------------------------------rate-limit for vlanPort
rcVlanPortRateLimitTable OBJECT-TYPE
    SYNTAX SEQUENCE OF RcVlanPortRateLimitEntry
    MAX-ACCESS not-accessible
    STATUS current
    DESCRIPTION
      "A table of rate-limit for vlanPort and associated properties."
    ::= { rcRateLimit 5}

rcVlanPortRateLimitEntry OBJECT-TYPE
    SYNTAX      RcVlanPortRateLimitEntry
    MAX-ACCESS  not-accessible
    STATUS      current
    DESCRIPTION
       "Table entry for rate-limit of vlanPort and status information."
    INDEX { rcVlanPortRateLimitPortIndex,rcVlanPortRateLimitPortRule, rcVlanPortRateLimitVlanIndex }
    ::= { rcVlanPortRateLimitTable 1 }

RcVlanPortRateLimitEntry ::= SEQUENCE
{
    rcVlanPortRateLimitPortIndex	INTEGER,
    rcVlanPortRateLimitPortRule     INTEGER,
    rcVlanPortRateLimitVlanIndex    INTEGER,
    rcVlanPortRateLimitRate    		INTEGER,
    rcVlanPortRateLimitBurst     	INTEGER,
    rcVlanPortRateLimitRowStatus    RowStatus
}

rcVlanPortRateLimitPortIndex   	OBJECT-TYPE
     SYNTAX    INTEGER
     ACCESS    not-accessible
     STATUS    current
     DESCRIPTION
       "The value of ifIndex that identifies the rate-limit of port which based 1."
     ::= { rcVlanPortRateLimitEntry 1 }

rcVlanPortRateLimitPortRule   	OBJECT-TYPE
     SYNTAX    INTEGER { ingress(1), egress(2) }
     ACCESS    not-accessible
     STATUS    current
     DESCRIPTION
       "A rule of rate-limit for the port."
     ::= { rcVlanPortRateLimitEntry 2 }

rcVlanPortRateLimitVlanIndex  	OBJECT-TYPE
     SYNTAX    INTEGER (1..4094)
     ACCESS    not-accessible
     STATUS    current
     DESCRIPTION
       "The vlan ID which identifies the vlan  of rate limitation."
     ::= { rcVlanPortRateLimitEntry 3 }

rcVlanPortRateLimitRate 	OBJECT-TYPE
     SYNTAX    INTEGER
     UNITS     "kbps"
     ACCESS    read-create
     STATUS    current
     DESCRIPTION
       "The value is the input rate( kbps)"
     ::= { rcVlanPortRateLimitEntry 4 }

rcVlanPortRateLimitBurst 	OBJECT-TYPE
     SYNTAX    INTEGER
     UNITS     "kB"
     ACCESS    read-create
     STATUS    current
     DESCRIPTION
       "The value is the ingress burst( kB)"
     ::= { rcVlanPortRateLimitEntry 5 }

rcVlanPortRateLimitRowStatus  	OBJECT-TYPE
    SYNTAX      RowStatus
    MAX-ACCESS  read-create
    STATUS      current
    DESCRIPTION
      "The status of this entry."
    ::= { rcVlanPortRateLimitEntry 6 }
END
