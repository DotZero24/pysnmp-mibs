-- MibName=raisecomMultiSys
-- *****************************************************************
-- Version 1.0 Created 2011.01.07 by zengliang
-- This version of MIB is created just for the multi system.
--
-- Copyright(c) 2002-2012 by RAISECOM TECH, Ltd.
-- All rights reserved.
--
-- modify history
--
-- *****************************************************************
SWITCH-MULTISYS-MIB  DEFINITIONS ::= BEGIN

IMPORTS
        raisecomAgent
            FROM RAISECOM-BASE-MIB
        Unsigned32
        	FROM SNMPv2-SMI;

	raisecomMultiSys MODULE-IDENTITY
        LAST-UPDATED    "201101070000Z"
        ORGANIZATION    "Raisecom, Inc."
        CONTACT-INFO
                "       Raise Systems

                Postal: Beijing,
                        China

                   Tel: 86-010-82884499

                E-mail: support@raisecom.com"
        DESCRIPTION
                "Configuration of multi system object."
--
-- modify history
--
        REVISION    "201101070000Z"
        DESCRIPTION "The initial revision of this MIB."
                ::= { raisecomAgent 22}

--
-- groups in the MULTISYS MIB
--
raisecomMultiSysMibObjects    OBJECT IDENTIFIER ::= { raisecomMultiSys 1 }

--
-- raisecomMultiSysMibObjects
--
raisecomMultiSysGlobalGroup   OBJECT IDENTIFIER ::= { raisecomMultiSysMibObjects 1 }

--
-- raisecomMultiSysGlobalGroup
--
    raisecomMultiSysVerNum OBJECT-TYPE
        SYNTAX	Unsigned32
        MAX-ACCESS  read-only
        STATUS      current
        DESCRIPTION
           	"The maximum system version number device support."
        ::= { raisecomMultiSysGlobalGroup 1 }

    raisecomMultiSysOverWriteVer OBJECT-TYPE
        SYNTAX	Unsigned32
        MAX-ACCESS  read-write
        STATUS      current
        DESCRIPTION
           	"When download new version to device,use this mib object to
           	 choose which system version existed will be overwrited."
        ::= { raisecomMultiSysGlobalGroup 2 }

    raisecomMultiSysUploadVer OBJECT-TYPE
        SYNTAX	Unsigned32
        MAX-ACCESS  read-write
        STATUS      current
        DESCRIPTION
           	"When upload new version to server,use this mib object to
           	 choose which system version existed will be uploaded."
        ::= { raisecomMultiSysGlobalGroup 3 }

    raisecomMultiSysNextBootVer OBJECT-TYPE
        SYNTAX	Unsigned32
        MAX-ACCESS  read-write
        STATUS      current
        DESCRIPTION
           	"Use this mib object to choose which system version existed
           	 will be booted when device is rebooted."
        ::= { raisecomMultiSysGlobalGroup 4 }


--
-- raisecomMultiSysVerTable
--
    raisecomMultiSysVerTable OBJECT-TYPE
        SYNTAX SEQUENCE OF RaisecomMultiSysVerEntry
        MAX-ACCESS not-accessible
        STATUS current
        DESCRIPTION
            "Multi system version table."
        ::= { raisecomMultiSysMibObjects 2 }

    raisecomMultiSysVerEntry OBJECT-TYPE
        SYNTAX RaisecomMultiSysVerEntry
        MAX-ACCESS not-accessible
        STATUS current
        DESCRIPTION
            "Multi system version entry."
        INDEX { raisecomMultiSysVerIndex }
        ::= { raisecomMultiSysVerTable 1 }

    RaisecomMultiSysVerEntry ::= SEQUENCE {
        raisecomMultiSysVerIndex            Unsigned32,
        raisecomMultiSysVerName             OCTET STRING (SIZE (64)),
        raisecomMultiSysVerSize          	Unsigned32
        }

    raisecomMultiSysVerIndex OBJECT-TYPE
        SYNTAX  Unsigned32
        MAX-ACCESS not-accessible
        STATUS current
        DESCRIPTION
            "The index of multi system version."
        ::= { raisecomMultiSysVerEntry 1 }

    raisecomMultiSysVerName OBJECT-TYPE
        SYNTAX  OCTET STRING (SIZE (64))
        MAX-ACCESS read-only
        STATUS current
        DESCRIPTION
            "The name of multi system version."
        ::= { raisecomMultiSysVerEntry 2 }

    raisecomMultiSysVerSize OBJECT-TYPE
        SYNTAX  Unsigned32
   	    MAX-ACCESS read-only
        STATUS current
        DESCRIPTION
            "The size of multi system version."
        ::= { raisecomMultiSysVerEntry 3 }
END
