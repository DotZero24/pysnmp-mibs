-- *****************************************************************
-- RAISECOM-EXTLOOPBACK-MIB.mib
--
-- Mar. 2009, wangyuhang
--
-- Copyright(c) 2009-2010 by RAISECOM TECH, Ltd.
-- All rights reserved.
-- *****************************************************************


RAISECOM-EXTLOOPBACK-MIB DEFINITIONS ::= BEGIN
IMPORTS
    Integer32,
    Counter32,
    Unsigned32,
    Gauge32,
    MacAddress                          FROM SNMPv2-TC     -- [RFC2579]
    InterfaceIndex					    FROM IF-MIB        -- [RFC2863]
    EnableVar                           FROM SWITCH-TC
    VlanId     		                	FROM Q-BRIDGE-MIB
    iscomSwitch                         FROM RAISECOM-BASE-MIB
    ;
rcExtLoopback  MODULE-IDENTITY
    LAST-UPDATED   "200711020000Z"
    ORGANIZATION   "Raisecom, Inc."
    CONTACT-INFO
                "       Raise Systems

                Postal: Beijing,
                        China

                   Tel: 86-010-82884499

                E-mail: wangyuhang@raisecom.com"
    DESCRIPTION
        "This MIB module defines objects to rcExtLoopback "
        REVISION   "200711020000Z"
        DESCRIPTION
            "The initial revision of this MIB."
        ::={ iscomSwitch  45 }
--
--
RcExtLoopbackMode ::= TEXTUAL-CONVENTION
    STATUS      current
    DESCRIPTION
       "        "
    REFERENCE
       "rcExtLoopback"
    SYNTAX      INTEGER {
                  disable          (1),
                  port     		   (2),
                  dmac		       (3),
                  smac		       (4),
                  cvlan			   (5),
                  svlan			   (6),
                  dvlan			   (7)
                }
--

--groupsType
    rcExtloopbackObjectsGroup	OBJECT IDENTIFIER ::= {rcExtLoopback 1}
    rcExtloopbackConfigGroup	OBJECT IDENTIFIER ::= {rcExtLoopback 2}

 --rcExtloopbackObjectsGroup
 		--rcExtLoopbackBMDMacTransEnable

    rcExtLoopbackBMDMacTransEnable       OBJECT-TYPE
	SYNTAX      EnableVar
    MAX-ACCESS  read-write
    STATUS      current
    DESCRIPTION
            "The mode of broadcast-mulitcast dmac transform"
    ::= { rcExtloopbackObjectsGroup 1 }
--OperConfigTable--
      --rcExtloopbackConfigGroup
		--rcExtLoopbackTable
			--rcExtLoopbackEntry
				--rcExtLoopbackPortIndex
				--rcExtLoopbackDMac
				--rcExtLoopbackSMac
				--rcExtLoopbackSVlan
				--rcExtLoopbackCVlan
				--rcExtLoopbackTime
				--rcExtLoopbackMode



rcExtLoopbackTable  OBJECT-TYPE
    SYNTAX      SEQUENCE OF RcExtLoopbackEntry
    MAX-ACCESS  not-accessible
    STATUS      current
    DESCRIPTION
        "This table contains sla  control data."
    ::= { rcExtloopbackConfigGroup 1 }

rcExtLoopbackEntry   OBJECT-TYPE
    SYNTAX      RcExtLoopbackEntry
    MAX-ACCESS  not-accessible
    STATUS      current
    DESCRIPTION
        ""
	INDEX        { rcExtLoopbackPortIndex }
    ::={ rcExtLoopbackTable 1 }

RcExtLoopbackEntry ::= SEQUENCE {
        rcExtLoopbackPortIndex				     INTEGER,
    	rcExtLoopbackDMac				     	 MacAddress,
    	rcExtLoopbackSMac		             	 MacAddress,
	    rcExtLoopbackSVlan                       VlanId,
	    rcExtLoopbackCVlan                       VlanId,
	    rcExtLoopbackTime		                 INTEGER,
	    rcExtLoopbackMode                     	 RcExtLoopbackMode
	 	    }

rcExtLoopbackPortIndex       OBJECT-TYPE
	SYNTAX      INTEGER
	MAX-ACCESS  not-accessible
    STATUS      current
    DESCRIPTION
            "An index based on the equipment port number."
    ::= { rcExtLoopbackEntry 1 }

rcExtLoopbackDMac       OBJECT-TYPE
	SYNTAX      MacAddress
	MAX-ACCESS  read-write
    STATUS      current
    DESCRIPTION
            "The packets which is based on this DMAC rule are loopback."
   ::= { rcExtLoopbackEntry 2 }

rcExtLoopbackSMac       OBJECT-TYPE
	SYNTAX      MacAddress
    MAX-ACCESS  read-write
    STATUS      current
    DESCRIPTION
            "The packets which is based on this SMAC rule are loopback."
    ::= { rcExtLoopbackEntry 3 }

rcExtLoopbackSVlan       OBJECT-TYPE
	SYNTAX      VlanId
	MAX-ACCESS  read-write
    STATUS      current
    DESCRIPTION
          "The packets which is based on this SVLAN rule are loopback."
    ::= { rcExtLoopbackEntry 4 }

rcExtLoopbackCVlan       OBJECT-TYPE
	SYNTAX      VlanId
    MAX-ACCESS  read-write
    STATUS      current
    DESCRIPTION
            "The packets which is based on this CVLAN rule are loopback."
    ::= { rcExtLoopbackEntry 5 }

rcExtLoopbackTime       OBJECT-TYPE
	SYNTAX      INTEGER
	MAX-ACCESS  read-write
    STATUS      current
    DESCRIPTION
            "How long loopback will last. '0' indicates forever."
    ::= { rcExtLoopbackEntry 6 }


rcExtLoopbackMode       OBJECT-TYPE
	SYNTAX      RcExtLoopbackMode
    MAX-ACCESS  read-write
    STATUS      current
    DESCRIPTION
            "The on-off loopback function.based on one of rules ."
    ::= { rcExtLoopbackEntry 7 }



END
