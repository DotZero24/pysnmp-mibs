--MibName=rcMacConfig
-- *****************************************************************
-- RAISECOM-VLANMACCOPY-MIB.MIB:  Raisecom Vlan Mac Copy MIB file
--
-- February 2009, qiyun
--
-- Copyright (c) 2003-2005 by RAISECOM TECH, Ltd.
-- All rights reserved.
--
--modify history
-- *****************************************************************
RAISECOM-VLANMACCOPY-MIB  DEFINITIONS ::= BEGIN

	IMPORTS
        iscomSwitch             FROM RAISECOM-BASE-MIB
       	Vlanset                 FROM SWITCH-TC
       	rcPortIndex          	FROM SWITCH-SYSTEM-MIB
        RowStatus      	        FROM SNMPv2-TC;
        rcMacConfig  		MODULE-IDENTITY
        LAST-UPDATED    "200809230000Z"
        ORGANIZATION    "Raisecom, Inc."
        CONTACT-INFO
                "       Raise Systems

                Postal: Beijing,
                        China

                   Tel: 86-010-82884499"
        DESCRIPTION
                "description of Mac binding object."
                ::= { iscomSwitch 3}


  	rcVlanMacCopyMibObjects    OBJECT IDENTIFIER ::= { rcMacConfig 5 }

--rcVlanMacCopyTable--
--rcMacConfig
    --rcVlanMacCopy
		-- rcVlanMacCopyMibObjects
			--rcVlanMacCopyTable
				--rcVlanMacCopyEntry
				    --rcMacCopyTableIndex
					--rcMacCopyDestVlanList
					--rcMacCopySourceVlanList
					--rcMacCopyRowStatus

	rcVlanMacCopyTable OBJECT-TYPE
        SYNTAX SEQUENCE OF RcVlanMacCopyEntry
        MAX-ACCESS not-accessible
        STATUS current
        DESCRIPTION
            "A table of MAC address copy status information between different vlan. "
        ::= { rcVlanMacCopyMibObjects 1}

    rcVlanMacCopyEntry OBJECT-TYPE
        SYNTAX RcVlanMacCopyEntry
        MAX-ACCESS not-accessible
        STATUS current
        DESCRIPTION
            "Table entry for MAC address copy status information."
        INDEX { rcPortIndex , rcMacCopyTableIndex }
        ::= { rcVlanMacCopyTable 1 }

  	RcVlanMacCopyEntry ::= SEQUENCE {
        rcMacCopyTableIndex              INTEGER,
        rcMacCopyDestVlanList         	 Vlanset,
        rcMacCopySourceVlanList          Vlanset,
        rcMacCopyRowStatus               RowStatus
    	}

    rcMacCopyTableIndex   OBJECT-TYPE
        SYNTAX    INTEGER
        ACCESS    not-accessible
        STATUS    current
        DESCRIPTION
             "Index of mac copy table."
        ::= { rcVlanMacCopyEntry 1 }


    rcMacCopyDestVlanList   OBJECT-TYPE
        SYNTAX    Vlanset
        ACCESS    read-create
        STATUS    current
        DESCRIPTION
             "The dest vlan List that the MAC address copy to."
        ::= { rcVlanMacCopyEntry 2 }

	rcMacCopySourceVlanList   OBJECT-TYPE
	  	SYNTAX    Vlanset
	  	ACCESS    read-create
	  	STATUS    current
	  	DESCRIPTION
	         "The source vlan List that the MAC address copy from."
	  	::= { rcVlanMacCopyEntry 3 }

	 rcMacCopyRowStatus   OBJECT-TYPE
	  	SYNTAX      RowStatus
	  	MAX-ACCESS  read-create
	  	STATUS      current
	  	DESCRIPTION
	         "The status of this entry."
	  	::= { rcVlanMacCopyEntry 4 }

END
