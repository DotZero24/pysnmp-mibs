-- MibName=raisecomKeepaliveToSNMPManagerGroup
-- =======================================================================
-- Version info
--
-- Version 0.1 Created 2007.07.09 by LIAOBIN
-- Copyright(c) 2003-2007 by RAISECOM TECH, Ltd.
-- =======================================================================

-- ===========================================================================

--
-- RAISECOM keepalive management objects
--

RAISECOM-KEEPALIVE-MIB DEFINITIONS ::= BEGIN

    IMPORTS
		MODULE-IDENTITY,
		OBJECT-TYPE,
		NOTIFICATION-TYPE ,
		Integer32,
		IpAddress,
		Counter32,
		Unsigned32
			FROM SNMPv2-SMI
		DisplayString,
		TimeStamp,
		RowStatus,
		TruthValue
			FROM SNMPv2-TC
		DateAndTime,
		EnableVar
			FROM SWITCH-TC
		raisecomAgent
			FROM RAISECOM-BASE-MIB

		rcL3IpSubnetIfIndex,rcL3IpSubnetIpAddress,rcL3IpSubnetMask
         FROM SWITCH-L3-MIB
    sysName,sysObjectID
         FROM RFC1213-MIB
    rcSwitchMacAddress,rcSwitchRoseVersion, rcSwitchHardwareVersion
         FROM SWITCH-SYSTEM-MIB

		raisecomCommonManagement
			FROM RAISECOM-COMMON-MANAGEMENT-MIB;

	raisecomKeepaliveToSNMPManagerGroup    MODULE-IDENTITY
		LAST-UPDATED 	"200707090000Z"
		ORGANIZATION 	"RAISECOM TECH, Ltd."
		CONTACT-INFO 	"www.raisecom.com"
		DESCRIPTION
		    "The MIB module defining objects for SNMP keepalive functions"
		::= { raisecomCommonManagement  6}

-- raisecomKeepaliveToSNMPManagerGroup

 	raisecomKeepaliveMibObjects OBJECT IDENTIFIER ::= { raisecomKeepaliveToSNMPManagerGroup 1 }
	raisecomKeepaliveTraps   OBJECT IDENTIFIER ::= { raisecomKeepaliveToSNMPManagerGroup 2 }

	raisecomKeepaliveTrapEnable  OBJECT-TYPE
  	SYNTAX          INTEGER{
        			enable(1),
        			disable(2),
        			pause(3)
        			}
        MAX-ACCESS read-write
        STATUS current
        DESCRIPTION
            "Indicates whether keepalive traps should be generated periodically.Disable
            and pause indicate keepalive traps should not be generated.If the value of
            this object is disable,it allow to be config loaded.If user makes this object
            disable and saves config,keepalive trap will not be generated after load
            config.If this object is pause,it don't allow to be config loaded."
        DEFVAL	{ enable }
    	::= { raisecomKeepaliveMibObjects 1 }


	raisecomKeepaliveTrapInterval  OBJECT-TYPE
        SYNTAX        INTEGER (120 .. 28800)
        UNITS         "seconds"
        MAX-ACCESS    read-write
        STATUS        current
        DESCRIPTION   "The value of this object indicates number of
                       seconds between the transmission of keepalive
                       trap."
        DEFVAL { 300 }
        ::= { raisecomKeepaliveMibObjects 2 }

  raisecomKeepaliveTrapCounter  OBJECT-TYPE
        SYNTAX        Counter32
        MAX-ACCESS    read-only
        STATUS        current
        DESCRIPTION   "The value of this object indicates number of
                       keepalive trap have sent."
        ::= { raisecomKeepaliveMibObjects 3}

   raisecomKeepalive NOTIFICATION-TYPE
           OBJECTS {rcL3IpSubnetIfIndex,rcL3IpSubnetIpAddress,rcL3IpSubnetMask,sysName,sysObjectID,
           rcSwitchMacAddress,rcSwitchRoseVersion, rcSwitchHardwareVersion}
           STATUS  current
           DESCRIPTION
               "notify snmp manager that rcL3IpSubnetIp and other information periodically."
       ::= { raisecomKeepaliveTraps 1 }

END
