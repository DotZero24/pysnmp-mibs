--MibName=rcFilter
-- *****************************************************************
-- switch-filter-mib.MIB:	 switch filter MIB file
--
-- Apri 2005, yingjiangang
--
-- Copyright (c) 1994-2004,	2001 by	Raisecom, Inc.
-- All rights reserved.
--
-- *****************************************************************

SWITCH-FILTER-MIB DEFINITIONS ::= BEGIN

IMPORTS
       Counter64
                FROM SNMPv2-SMI
        iscomSwitch
         		FROM RAISECOM-BASE-MIB
        RowStatus,TruthValue
                FROM SNMPv2-TC
        EnableVar
                FROM SWITCH-TC
        PortList
            FROM SWITCH-TC
		    Gauge32
				    FROM SNMPv2-SMI;

        rcFilter MODULE-IDENTITY
        LAST-UPDATED    "200504120000Z"
        ORGANIZATION    "Raisecom, Inc."
        CONTACT-INFO
                "       Raise Systems

                Postal: Beijing,
                        China

                   Tel: 86-010-82884499

                E-mail: yuanqingguo@raisecom.com"
        DESCRIPTION
                "description of filter manage object."
                ::= { iscomSwitch 14}


-------------------------------------------------------------------------------
--	define groups in SWITCH-FILTER-MIB
------------------------------------------------------------------------------
	rcAclFilter		OBJECT IDENTIFIER ::= {	rcFilter 1 }
------------------------------------------------------------------------------

--The acl Filter--
	rcAclFilterAction OBJECT-TYPE
		SYNTAX	EnableVar
		ACCESS	read-write
		STATUS	current
		DESCRIPTION
			"The clause	describes whether the filter list is in effect."
	   ::= { rcAclFilter 1	}

	rcAclFilterNextIndex OBJECT-TYPE
		SYNTAX	INTEGER
		ACCESS	read-only
		STATUS	current
		DESCRIPTION
			"the next filter Index."
		::=	{ rcAclFilter 2 }

	rcAclFilterTable OBJECT-TYPE
		SYNTAX		SEQUENCE OF	RcAclFilterEntry
		MAX-ACCESS	not-accessible
		STATUS		current
		DESCRIPTION
			"A table of	acl filter."
		::=	{ rcAclFilter 3}

	rcAclFilterEntry OBJECT-TYPE
		SYNTAX		RcAclFilterEntry
		MAX-ACCESS	not-accessible
		STATUS		current
		DESCRIPTION
			"Table entry for acl filter	and	status information."
		INDEX {	rcAclFilterIndex }
		::=	{ rcAclFilterTable 1 }

	RcAclFilterEntry ::= SEQUENCE {
		rcAclFilterIndex			INTEGER,
		rcAclFilterAclType			INTEGER,
		rcAclFilterAclNumber		INTEGER,
		rcAclFilterIngressPort		INTEGER,
		rcAclFilterEgressPort		INTEGER,
		rcAclFilterVlan				INTEGER,
		rcAclFilterStatus			RowStatus,
		rcAclFilterHwStatus			EnableVar,
		rcAclFilterDoubleTagging	TruthValue,
		rcAclFilterVlanType			INTEGER,
        rcAclFilterStatEnable       EnableVar,
        rcAclFilterStatHwStatus     EnableVar,
        rcAclFilterIngressPortList  PortList,
        }

	rcAclFilterIndex OBJECT-TYPE
		SYNTAX	INTEGER
		ACCESS	not-accessible
		STATUS	current
		DESCRIPTION
			"The value of this object uniquely identifies this filter entry."
		::=	{ rcAclFilterEntry 1 }

	rcAclFilterAclType OBJECT-TYPE
		SYNTAX	INTEGER
		{
			ip-acl(1),
			mac-acl(2),
			user-acl(3)
		}
		ACCESS	read-create
		STATUS	current
		DESCRIPTION
			"The type of access	list."
		::=	{ rcAclFilterEntry 2 }

	rcAclFilterAclNumber OBJECT-TYPE
		SYNTAX	INTEGER
		ACCESS	read-create
		STATUS	current
		DESCRIPTION
			"The index nember of the access list which specified
			 by rcAclFilterAclType."
		::=	{ rcAclFilterEntry 3 }

	rcAclFilterIngressPort OBJECT-TYPE
		SYNTAX	INTEGER
		ACCESS	read-create
		STATUS	current
		DESCRIPTION
			"The port from which the packets are received."
		::=	{ rcAclFilterEntry 4 }

	rcAclFilterEgressPort OBJECT-TYPE
		SYNTAX	INTEGER
		ACCESS	read-create
		STATUS	current
		DESCRIPTION
			"The port to which the packets are sent."
		::=	{ rcAclFilterEntry 5 }

	rcAclFilterVlan	OBJECT-TYPE
		SYNTAX	INTEGER(0..4094)
		ACCESS	read-create
		STATUS	current
		DESCRIPTION
			"The bitmap of the VlanId list."
		::=	{ rcAclFilterEntry 6 }

	rcAclFilterStatus OBJECT-TYPE
		SYNTAX	RowStatus
		ACCESS	read-create
		STATUS	current
		DESCRIPTION
			"The row status	of this	entry."
		::=	{ rcAclFilterEntry 7 }

	rcAclFilterHwStatus OBJECT-TYPE
		SYNTAX	EnableVar
		ACCESS	read-only
		STATUS	current
		DESCRIPTION
			"in hardware or not."
		::=	{ rcAclFilterEntry 8 }

	rcAclFilterDoubleTagging OBJECT-TYPE
		SYNTAX	TruthValue
		ACCESS	read-create
		STATUS	current
		DESCRIPTION
			"Double tagging mode true or false."
		::=	{ rcAclFilterEntry 9 }


	rcAclFilterVlanType OBJECT-TYPE
		SYNTAX	INTEGER
		{
			inner(1),
			outer(2)
		}
		ACCESS	read-create
		STATUS	current
		DESCRIPTION
			"Vlan Type, inner(1) or outer(2)."
		::=	{ rcAclFilterEntry 10 }
	rcAclFilterStatEnable OBJECT-TYPE
	    SYNTAX    EnableVar
	    ACCESS    read-create
	    STATUS    current
	    DESCRIPTION
	      "statistics or not."
	    ::= { rcAclFilterEntry 11}

	rcAclFilterStatHwStatus OBJECT-TYPE
	    SYNTAX    EnableVar
	    ACCESS    read-only
	    STATUS    current
	    DESCRIPTION
	      "in hardware or not."
	    ::= { rcAclFilterEntry 12}

	rcAclFilterIngressPortList OBJECT-TYPE
	    SYNTAX    PortList
	    ACCESS    read-write
	    STATUS    current
	    DESCRIPTION
	      "Mac-access-list ingress portlist"
	    ::= { rcAclFilterEntry 14}
	rcAclFilterStatisticsTable OBJECT-TYPE
	    SYNTAX    SEQUENCE OF RcAclFilterStatisticsEntry
	    MAX-ACCESS  not-accessible
	    STATUS      current
	    DESCRIPTION
	      "A table of acl filter statistics."
	    ::= { rcAclFilter 4}

	rcAclFilterStatisticsEntry OBJECT-TYPE
	    SYNTAX      RcAclFilterStatisticsEntry
	    MAX-ACCESS  not-accessible
	    STATUS      current
	    DESCRIPTION
	      "Table entry for acl filter statistics ."
	    AUGMENTS { rcAclFilterEntry }
	    ::= { rcAclFilterStatisticsTable 1 }

	RcAclFilterStatisticsEntry ::= SEQUENCE
	{
	    rcAclFilterCounterReset   EnableVar,
	    rcAclFilterCounterPkt64   Counter64,
	    rcAclFilterCounterByte64  Counter64,
        rcAclFilterCounterStatisticUnit INTEGER
	}

	 rcAclFilterCounterReset OBJECT-TYPE
	    SYNTAX     EnableVar
	    ACCESS     read-write
	    STATUS     current
	    DESCRIPTION
	      "clear the statistics."
	    ::= { rcAclFilterStatisticsEntry 1 }

	rcAclFilterCounterPkt64 OBJECT-TYPE
	    SYNTAX     Counter64
	    ACCESS     read-only
	    STATUS     current
	    DESCRIPTION
	      "The pkt64 of the filter statistics."
	    ::= { rcAclFilterStatisticsEntry 2 }

	rcAclFilterCounterByte64  OBJECT-TYPE
	    SYNTAX     Counter64
	    ACCESS     read-only
	    STATUS     current
	    DESCRIPTION
	      "The Byte64 of the filter statistics."
	    ::= { rcAclFilterStatisticsEntry 3 }
	rcAclFilterCounterStatisticUnit OBJECT-TYPE
	    SYNTAX     INTEGER
	    ACCESS     read-only
	    STATUS     current
	    DESCRIPTION
	      "the filter statistics unit."
	    ::= { rcAclFilterStatisticsEntry 4 }
END
