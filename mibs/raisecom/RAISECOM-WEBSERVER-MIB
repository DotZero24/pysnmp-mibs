--MibName=raisecomWebServer
-- *****************************************************************
-- raisecom-webserver-mib.mib:  Raisecom WEB SERVER MIB file
--
-- Aug 2011, zhangjiguang
--
-- Copyright (c) 1994-2000, 2001 by Raisecom, Inc.
-- All rights reserved.
--
-- *****************************************************************

RAISECOM-WEBSERVER-MIB DEFINITIONS ::= BEGIN

IMPORTS
    MODULE-IDENTITY, OBJECT-TYPE,
    Integer32     	 			           FROM SNMPv2-SMI
    EnableVar	                        FROM SWITCH-TC
    raisecomAgent                    FROM RAISECOM-BASE-MIB;
    raisecomWebServer MODULE-IDENTITY
    LAST-UPDATED "201102180000Z"
    ORGANIZATION "raisecom Group"
    CONTACT-INFO
                "       Raise Systems

                Postal: Beijing,
                        China

                   Tel: 86-010-82884499

                E-mail: zhangjiguang@raisecom.com"
    DESCRIPTION
            "The MIB module for Web Module."
    ::= { raisecomAgent 46}

raisecomWebServerNotifications	OBJECT IDENTIFIER ::= {	raisecomWebServer 1 }
raisecomWebServerObjects			OBJECT IDENTIFIER ::= {	raisecomWebServer 2 }
raisecomWebServerConformance		OBJECT IDENTIFIER ::= {	raisecomWebServer 3 }

raisecomWebServerScalar		OBJECT IDENTIFIER ::= {	raisecomWebServerObjects 1 }
raisecomHttpClientsTable		OBJECT IDENTIFIER ::= {	raisecomWebServerObjects 2 }

--
-- raisecomWebServerScalar
--

raisecomHttpServerEnable OBJECT-TYPE
        SYNTAX EnableVar
        MAX-ACCESS read-write
        STATUS current
        DESCRIPTION
            "The state of global http server.
             It has two values,one is enable(1),which indicates that the system start http server;
             the other is disable(2) that means web server is invalid in this system.
             The default value is disable(2)."
        DEFVAL { disable }
        ::= { raisecomWebServerScalar 1 }

raisecomHttpsServerEnable OBJECT-TYPE
        SYNTAX EnableVar
        MAX-ACCESS read-write
        STATUS current
        DESCRIPTION
            "The state of global https server.
             It has two values,one is enable(1),which indicates that the system start https server;
             the other is disable(2) that means https is invalid in this system.
             The default value is disable(2)."
        DEFVAL { disable }
        ::= { raisecomWebServerScalar 2 }

raisecomHttpPort OBJECT-TYPE
        SYNTAX        INTEGER(0..65535)
		  MAX-ACCESS  read-write
        STATUS      current
        DESCRIPTION
               "The port value for http service.
               The default value is 80, the vlaue user set must be between 0 to 65535."
        DEFVAL { 80 }
        ::= { raisecomWebServerScalar 3 }

raisecomHttpsPort OBJECT-TYPE
        SYNTAX        INTEGER(0..65535)
		  MAX-ACCESS  read-write
        STATUS      current
        DESCRIPTION
               "The port value for https service.
               The default value is 443, the vlaue user set must be between 0 to 65535."
        DEFVAL { 443 }
        ::= { raisecomWebServerScalar 4 }

raisecomHttpAuth OBJECT-TYPE
       SYNTAX INTEGER
                {
                    local(1),
                    radius (2),
                    tacacs(3)
                }
        MAX-ACCESS read-write
        STATUS current
        DESCRIPTION
             "The method of web user authentication.
             The type local(1) is for the local authentication.
             The type radius(2) is for the radius authentication.
             The type tacacs(3) is for the tacacs authentication.
             The default type is local."
        DEFVAL { 1 }
        ::= { raisecomWebServerScalar 5 }

raisecomHttpTimeout OBJECT-TYPE
        SYNTAX INTEGER(300..1200)
        MAX-ACCESS read-write
        STATUS current
        DESCRIPTION
           "if the client do nothing within this timeout after logon, he must re-logon after the time out."
        DEFVAL { 400 }
        ::= { raisecomWebServerScalar 6 }

--
--raisecomHttpClientsTable
--
          raisecomHttpClientsTable OBJECT-TYPE
              SYNTAX  SEQUENCE OF raisecomHttpClientsEntry
              MAX-ACCESS  not-accessible
              STATUS  current
              DESCRIPTION
                      "A table that contains web client information, include ID, IP, name."
              ::= { raisecomWebServerObjects 2 }

          raisecomHttpClientsEntry OBJECT-TYPE
              SYNTAX  raisecomHttpClientsEntry
              MAX-ACCESS  not-accessible
              STATUS  current
              DESCRIPTION
                      "An entry that contains web client information, include ID, IP, name."
              INDEX   { raisecomHttpClientsIndex }
              ::= { raisecomHttpClientsTable 1 }

          raisecomHttpClientsEntry ::=
              SEQUENCE {
                  raisecomHttpClientsIndex	   INTEGER,
                  raisecomHttpClientsID           INTEGER,
                  raisecomHttpClientsIP           IpAddress,
                  raisecomHttpClientsName      OCTET STRING
                  }

          raisecomHttpClientsIndex OBJECT-TYPE
              SYNTAX  INTEGER
              MAX-ACCESS  not-accessible
              STATUS  current
              DESCRIPTION
                      "The index of web client."
              ::= { raisecomHttpClientsEntry 1 }

          raisecomHttpClientsID OBJECT-TYPE
              SYNTAX  INTEGER
              MAX-ACCESS  read-only
              STATUS  current
              DESCRIPTION
                      "The ID of web client."
              ::= { raisecomHttpClientsEntry 2 }

           raisecomHttpClientsIP OBJECT-TYPE
              SYNTAX  IpAddress
              MAX-ACCESS  read-only
              STATUS  current
              DESCRIPTION
                      "The ip address of web client."
              ::= { raisecomHttpClientsEntry 3 }

          raisecomHttpClientsName OBJECT-TYPE
              SYNTAX  OCTET STRING
              MAX-ACCESS  read-only
              STATUS  current
              DESCRIPTION
                      "The name of web client."
              ::= { raisecomHttpClientsEntry 4 }

END
