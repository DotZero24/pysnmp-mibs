-- *****************************************************************
-- RAISECOM-ARP-MIB.mib
--
--  January 2012, wuxia
--
-- Copyright(c) 2011-2013 by RAISECOM TECH, Ltd.
-- All rights reserved.
-- *****************************************************************

--MibName=raisecomArp
RAISECOM-ARP-MIB DEFINITIONS ::= BEGIN

IMPORTS
    MODULE-IDENTITY, OBJECT-TYPE, Counter32, Gauge32,
    Integer32, Unsigned32, IpAddress, mib-2
                 FROM SNMPv2-SMI
    TEXTUAL-CONVENTION, TruthValue, RowStatus, TimeStamp
                 FROM SNMPv2-TC
    EnableVar	 FROM SWITCH-TC
    InterfaceIndex
                 FROM IF-MIB
    raisecomAgent
                 FROM RAISECOM-BASE-MIB;

    raisecomArp MODULE-IDENTITY
        LAST-UPDATED    "201201100000Z"  -- Jan 10, 2012
        ORGANIZATION    "Raisecom, Inc."
        CONTACT-INFO
                "       Raise Systems
                        Postal: Beijing, China
                        Tel: 86-010-82884499
                        E-mail: support@raisecom.com"

        DESCRIPTION     "This MIB module defines objects to Arp."

        REVISION        "201201100000Z"  -- Jan 10, 2012
        DESCRIPTION     "Initial MIB creation."

        ::= { raisecomAgent 74}

------------------------------------------------------------------------------
--  Define groups in RAISECOM-ARP-MIB
------------------------------------------------------------------------------

    raisecomArpTable  OBJECT IDENTIFIER ::= { raisecomArp 1 }
    raisecomArpScalarGroup    OBJECT IDENTIFIER ::= { raisecomArp 2 }

------------------------------------------------------------------------------
--  Define groups in raisecomArpTable
------------------------------------------------------------------------------
    raisecomArpIfTable  OBJECT IDENTIFIER ::= { raisecomArpTable 1 }
------------------------------------------------------------------------------



--raisecomArpIfTable
raisecomArpIfTable OBJECT-TYPE
    SYNTAX SEQUENCE OF raisecomArpIfEntry
    MAX-ACCESS not-accessible
    STATUS current
    DESCRIPTION
        "The ARP Interface Table ."
    ::=  { raisecomArpTable 1 }

raisecomArpIfEntry OBJECT-TYPE
    SYNTAX raisecomArpIfEntry
    MAX-ACCESS not-accessible
    STATUS current
    DESCRIPTION
        "The ARP Interface Table entry."
    INDEX {raisecomArpIfIndex}
    ::=  {raisecomArpIfTable 1 }

raisecomArpIfEntry ::= SEQUENCE {
    raisecomArpIfIndex    InterfaceIndex,
    raisecomArpMaxLearnNum Unsigned32
    }

raisecomArpIfIndex OBJECT-TYPE
    SYNTAX InterfaceIndex
    MAX-ACCESS not-accessible
    STATUS current
    DESCRIPTION
        "The index value that uniquely identifies the interface to which this entry is applicable."
    ::=  { raisecomArpIfEntry 1 }

raisecomArpMaxLearnNum  OBJECT-TYPE
    SYNTAX Unsigned32
    MAX-ACCESS read-create
    STATUS current
    DESCRIPTION
        "The max number of arp."
    ::= { raisecomArpIfEntry  2 }

--raisecomArpScalarGroup
raisecomArpLearnMode OBJECT-TYPE
        SYNTAX    INTEGER{learn-all (1), learn-reply-only (2)}
        MAX-ACCESS read-write
        STATUS     current
        DESCRIPTION
            "the arp learn mode"
        ::= { raisecomArpScalarGroup 1 }

END
