-- MibName=rcPPPoEAgent
-- *****************************************************************
-- RAISECOM-VLAN-MIB.MIB:  Raisecom PPPoEAgent MIB file
-- NOV 2008, huangxiyuan
--
-- Copyright (c) 2008 by Raisecom, Inc.
-- All rights reserved.
--
-- *****************************************************************
RAISECOM-PPPOEAGENT-MIB  DEFINITIONS ::= BEGIN

IMPORTS
        EnableVar      FROM SWITCH-TC
        ifIndex        FROM IF-MIB
        iscomSwitch	   FROM RAISECOM-BASE-MIB;


	rcPPPoEAgent MODULE-IDENTITY
        LAST-UPDATED    "200811100000Z"
        ORGANIZATION    "Raisecom, Inc."
        CONTACT-INFO
                "       Raise Systems

                Postal: Beijing, China

                   Tel: 86-010-82884499

                E-mail: support@raisecom.com"
        DESCRIPTION
                "description of PPPoEAgent object."
                ::= { iscomSwitch 47}

--
-- groups in the MIB
--

rcPPPoEAgentConfigAttachString    OBJECT-TYPE
        SYNTAX   OCTET STRING(SIZE(0..55))
        ACCESS   read-write
        STATUS   current
        DESCRIPTION
                 "PPPoE intermediate agent Circuit-ID attach-string"
        ::= { rcPPPoEAgent 1 }
-- config table--
rcPPPoEAgentConfigTable  OBJECT-TYPE
        SYNTAX   SEQUENCE OF rcPPPoEAgentConfigEntry
        ACCESS	 not-accessible
        STATUS   current
        DESCRIPTION
                 "This table provides objects to pppoe+ port config list"
        ::= { rcPPPoEAgent 2 }

rcPPPoEAgentConfigEntry  OBJECT-TYPE
        SYNTAX   rcPPPoEAgentConfigEntry
        ACCESS   not-accessible
        STATUS   current
        DESCRIPTION
                 "An entry in rcPPPoEAgentConfigTable"
        INDEX { ifIndex }
        ::= { rcPPPoEAgentConfigTable 1 }

rcPPPoEAgentConfigEntry ::= SEQUENCE {
		rcPPPoEAgentConfigPortEnable       EnableVar,
		rcPPPoEAgentConfigOverwriteEnable  EnableVar,
		rcPPPoEAgentConfigCircuitIDInfo	   OCTET STRING,
		rcPPPoEAgentConfigRemoteIDType	   INTEGER,
		rcPPPoEAgentConfigRemoteIDFormat   INTEGER,
		rcPPPoEAgentConfigPortTrust        INTEGER
}

rcPPPoEAgentConfigPortEnable  OBJECT-TYPE
		SYNTAX	EnableVar
		ACCESS	read-write
		STATUS	current
		DESCRIPTION
		    	"Enable PPPoE intermediate agent"
		::= { rcPPPoEAgentConfigEntry 1 }

rcPPPoEAgentConfigOverwriteEnable  OBJECT-TYPE
		SYNTAX	EnableVar
		ACCESS	read-write
		STATUS	current
		DESCRIPTION
		    	"Enable PPPoE intermediate agent overwrite the VST infomation"
		::= { rcPPPoEAgentConfigEntry 2 }

rcPPPoEAgentConfigCircuitIDInfo  OBJECT-TYPE
		SYNTAX	OCTET STRING(SIZE(0..63))
		ACCESS	read-write
		STATUS	current
		DESCRIPTION
		    	"Circuit-ID infomation of PPPoE intermediate agent"
		::= { rcPPPoEAgentConfigEntry 3 }

rcPPPoEAgentConfigRemoteIDType  OBJECT-TYPE
		SYNTAX	INTEGER{switch-mac(1), client-mac(2)}
		ACCESS	read-write
		STATUS	current
		DESCRIPTION
		    	"Remote-ID type of PPPoE intermediate agent"
		DEFVAL {switch-mac}
		::= { rcPPPoEAgentConfigEntry 4 }

rcPPPoEAgentConfigRemoteIDFormat  OBJECT-TYPE
		SYNTAX	INTEGER{binary(1), ascii(2)}
		ACCESS	read-write
		STATUS	current
		DESCRIPTION
		    	"Remote-ID format of PPPoE intermediate agent"
		DEFVAL {binary}
		::= { rcPPPoEAgentConfigEntry 5 }

rcPPPoEAgentConfigPortTrust  OBJECT-TYPE
		SYNTAX	INTEGER{True(1), False(2)}
		ACCESS	read-write
		STATUS	current
		DESCRIPTION
		    	"Trust port of PPPoE intermediate agent"
		DEFVAL {True}
		::= { rcPPPoEAgentConfigEntry 6 }

-- statistic table

rcPPPoEAgentStatisticsTable  OBJECT-TYPE
        SYNTAX   SEQUENCE OF rcPPPoEAgentStatisticsEntry
        ACCESS	 not-accessible
        STATUS   current
        DESCRIPTION
                 "This table provides objects to pppoe+ port statistics list"
        ::= { rcPPPoEAgent 3 }

rcPPPoEAgentStatisticsEntry  OBJECT-TYPE
        SYNTAX   rcPPPoEAgentStatisticsEntry
        ACCESS   not-accessible
        STATUS   current
        DESCRIPTION
                 "An entry in rcPPPoEAgentStatisticsTable"
        INDEX { ifIndex }
        ::= { rcPPPoEAgentStatisticsTable 1 }

rcPPPoEAgentStatisticsEntry ::= SEQUENCE {
		rcPPPoEAgentStatisticsReset			 INTEGER,
		rcPPPoEAgentStatisticsPADIReceived	 INTEGER,
		rcPPPoEAgentStatisticsPADISend	     INTEGER,
		rcPPPoEAgentStatisticsPADRReceived	 INTEGER,
		rcPPPoEAgentStatisticsPADRSend	     INTEGER
}

rcPPPoEAgentStatisticsReset  OBJECT-TYPE
		SYNTAX	INTEGER {reset(1)}
		ACCESS	read-write
		STATUS	current
		DESCRIPTION
		    	"To reset PPPoE packet counter"
		::= { rcPPPoEAgentStatisticsEntry 1 }

rcPPPoEAgentStatisticsPADIReceived  OBJECT-TYPE
		SYNTAX	INTEGER
		ACCESS	read-only
		STATUS	current
		DESCRIPTION
		    	"Indicate how many PADI packet the CPU of switch had received"
		::= { rcPPPoEAgentStatisticsEntry 2 }

rcPPPoEAgentStatisticsPADISend  OBJECT-TYPE
		SYNTAX	INTEGER
		ACCESS	read-only
		STATUS	current
		DESCRIPTION
		    	"Indicate how many PADI packet the CPU of switch had send"
		::= { rcPPPoEAgentStatisticsEntry 3 }

rcPPPoEAgentStatisticsPADRReceived  OBJECT-TYPE
		SYNTAX	INTEGER
		ACCESS	read-only
		STATUS	current
		DESCRIPTION
		    	"Indicate how many PADR packet the CPU of switch had received"
		::= { rcPPPoEAgentStatisticsEntry 4 }

rcPPPoEAgentStatisticsPADRSend  OBJECT-TYPE
		SYNTAX	INTEGER
		ACCESS	read-only
		STATUS	current
		DESCRIPTION
		    	"Indicate how many PADR packet the CPU of switch had send"
		::= { rcPPPoEAgentStatisticsEntry 5 }

rcPPPoEAgentConfigCircuitIDMode OBJECT-TYPE
        SYNTAX   INTEGER{switch(1), onu(2)}
        ACCESS   read-write
        STATUS   current
        DESCRIPTION
                 "PPPoE intermediate agent Circuit-ID padding mode"
        DEFVAL {switch}
        ::= { rcPPPoEAgent 4 }

rcPPPoEAgentConfigEnable OBJECT-TYPE
        SYNTAX   EnableVar
        ACCESS   read-write
        STATUS   current
        DESCRIPTION
                 "Indicates whether the global PPPoE Agent is enabled"
        ::= { rcPPPoEAgent 5 }

END
