-- File: RC002-INTERVAL-PERFORMANCE-STAT.my
-- Changes:
-- author:SunSuli

 RC002-INTERVAL-PERFORMANCE-STAT-MIB DEFINITIONS ::= BEGIN

    IMPORTS
		IpAddress, OBJECT-TYPE, MODULE-IDENTITY,
		NOTIFICATION-TYPE, Integer32,Counter32,Unsigned32
        	     FROM SNMPv2-SMI
		DisplayString,
		TimeStamp
		           FROM SNMPv2-TC
    rcftChassisIndex, rcftSlotIndex,rcftMibObjects,rcftSlotStat
       	     FROM RAISECOM-RCFT-MIB;

 	------------------线路侧光口性能统计的表------------------------
       rcftSlotWANFxPortCurrentTable OBJECT-TYPE
         SYNTAX  SEQUENCE OF RcftSlotWANFxPortCurrentEntry
         MAX-ACCESS  not-accessible
         STATUS  current
         DESCRIPTION
            "The Local device WAN FX Port Current table."
           ::= {rcftSlotStat 4}

       rcftSlotWANFxPortCurrentEntry OBJECT-TYPE
           SYNTAX  RcftSlotWANFxPortCurrentEntry
           MAX-ACCESS  not-accessible
           STATUS  current
           DESCRIPTION
              "An entry in the Local device WAN FX Port Current table."
           INDEX   {rcftChassisIndex,rcftSlotIndex,rcftSlotWANFxPortIndex}
            ::= { rcftSlotWANFxPortCurrentTable 1 }

       RcftSlotWANFxPortCurrentEntry ::=
           SEQUENCE {
           	   rcftSlotWANFxPortIndex				 INTEGER,
               rcftSlotWANFxPortCurrentTemperature	 OCTET STRING,
               rcftSlotWANFxPortCurrentVoltage     	 OCTET STRING,
               rcftSlotWANFxPortCurrentOffsetCurr    OCTET STRING,
               rcftSlotWANFxPortCurrentRecvPower     OCTET STRING,
               rcftSlotWANFxPortCurrentSendPower     OCTET STRING
           }

	    rcftSlotWANFxPortIndex OBJECT-TYPE
	    	SYNTAX INTEGER
	    	MAX-ACCESS read-only
	    	STATUS current
	    	DESCRIPTION
	    	"
	    		WAN Fx port index (1..2)
	    	"
	    	::= { rcftSlotWANFxPortCurrentEntry 1}

        rcftSlotWANFxPortCurrentTemperature OBJECT-TYPE
            SYNTAX  OCTET STRING(SIZE (0..20))
            MAX-ACCESS  read-only
            STATUS  current
            DESCRIPTION
               "this OBJECT indicates the average temperature in the current 15 minute interval."
             ::= { rcftSlotWANFxPortCurrentEntry 2 }

        rcftSlotWANFxPortCurrentVoltage OBJECT-TYPE
            SYNTAX  OCTET STRING(SIZE (0..20))
            MAX-ACCESS  read-only
            STATUS  current
            DESCRIPTION
               "This OBJECT indicates the averaget voltage in the current 15 minute interval."
             ::= { rcftSlotWANFxPortCurrentEntry 3 }

        rcftSlotWANFxPortCurrentOffsetCurr OBJECT-TYPE
            SYNTAX  OCTET STRING(SIZE (0..20))
            MAX-ACCESS  read-only
            STATUS  current
            DESCRIPTION
               "The object indicates the average offset current in the current
               15 minute interval."
            ::= { rcftSlotWANFxPortCurrentEntry 4 }

        rcftSlotWANFxPortCurrentRecvPower OBJECT-TYPE
            SYNTAX  OCTET STRING(SIZE (0..20))
            MAX-ACCESS  read-only
            STATUS  current
            DESCRIPTION
               "This object indicates the average receive power in the current
               15 minute interval."
            ::= { rcftSlotWANFxPortCurrentEntry 5 }

        rcftSlotWANFxPortCurrentSendPower OBJECT-TYPE
            SYNTAX  OCTET STRING(SIZE (0..20))
            MAX-ACCESS  read-only
            STATUS  current
            DESCRIPTION
               "This object indicates the average send power in the current
               15 minute interval."
              ::= { rcftSlotWANFxPortCurrentEntry 6 }

       rcftSlotWANFxPortIntervalTable OBJECT-TYPE
         SYNTAX  SEQUENCE OF RcftSlotWANFxPortIntervalEntry
         MAX-ACCESS  not-accessible
         STATUS  current
         DESCRIPTION
            "The Local device WAN FX Port interval table."
           ::= {rcftSlotStat 5}

       rcftSlotWANFxPortIntervalEntry OBJECT-TYPE
           SYNTAX  RcftSlotWANFxPortIntervalEntry
           MAX-ACCESS  not-accessible
           STATUS  current
           DESCRIPTION
              "An entry in the Local device WAN FX Port interval table."
           INDEX  { rcftChassisIndex,rcftSlotIndex,rcftSlotWANFxPortIndex,rcftSlotWANFxIntervalNumber}
            ::= { rcftSlotWANFxPortIntervalTable 1 }

       RcftSlotWANFxPortIntervalEntry ::=
           SEQUENCE {
           	   rcftSlotWANFxIntervalNumber 			 INTEGER,
               rcftSlotWANFxPortIntervalTemperature	 OCTET STRING,
               rcftSlotWANFxPortIntervalVoltage      OCTET STRING,
               rcftSlotWANFxPortIntervalOffsetCurr   OCTET STRING,
               rcftSlotWANFxPortIntervalRecvPower    OCTET STRING,
               rcftSlotWANFxPortIntervalSendPower    OCTET STRING
           }

	 	rcftSlotWANFxIntervalNumber OBJECT-TYPE
	 		SYNTAX INTEGER
	 		MAX-ACCESS  read-only
	 		STATUS current
	 		DESCRIPTION
	 		"
	 			WAN FX PORT 第几个十五分钟
	 		"
	 		::= { rcftSlotWANFxPortIntervalEntry 1 }


        rcftSlotWANFxPortIntervalTemperature OBJECT-TYPE
            SYNTAX  OCTET STRING(SIZE (0..20))
            MAX-ACCESS  read-only
            STATUS  current
            DESCRIPTION
               "this OBJECT indicates the average temperature in the interval 15 minute interval."
             ::= { rcftSlotWANFxPortIntervalEntry 2 }

        rcftSlotWANFxPortIntervalVoltage OBJECT-TYPE
            SYNTAX  OCTET STRING(SIZE (0..20))
            MAX-ACCESS  read-only
            STATUS  current
            DESCRIPTION
               "This OBJECT indicates the averaget voltage in the interval 15 minute interval."
             ::= { rcftSlotWANFxPortIntervalEntry 3 }

        rcftSlotWANFxPortIntervalOffsetCurr OBJECT-TYPE
            SYNTAX  OCTET STRING(SIZE (0..20))
            MAX-ACCESS  read-only
            STATUS  current
            DESCRIPTION
               "The object indicates the average offset interval in the interval
               15 minute interval."
            ::= { rcftSlotWANFxPortIntervalEntry 4 }

        rcftSlotWANFxPortIntervalRecvPower OBJECT-TYPE
            SYNTAX  OCTET STRING(SIZE (0..20))
            MAX-ACCESS  read-only
            STATUS  current
            DESCRIPTION
               "This object indicates the average receive power in the current
               15 minute interval."
            ::= { rcftSlotWANFxPortIntervalEntry 5 }

        rcftSlotWANFxPortIntervalSendPower OBJECT-TYPE
            SYNTAX  OCTET STRING(SIZE (0..20))
            MAX-ACCESS  read-only
            STATUS  current
            DESCRIPTION
               "This object indicates the average send power in the current
               15 minute interval."
            ::= { rcftSlotWANFxPortIntervalEntry 6 }

 	------------------客户侧光口性能统计的表------------------------
       rcftSlotLANFxPortCurrentTable OBJECT-TYPE
         SYNTAX  SEQUENCE OF RcftSlotLANFxPortCurrentEntry
         MAX-ACCESS  not-accessible
         STATUS  current
         DESCRIPTION
            "The Local device LAN FX Port Current table."
           ::= {rcftSlotStat 6}

       rcftSlotLANFxPortCurrentEntry OBJECT-TYPE
           SYNTAX  RcftSlotLANFxPortCurrentEntry
           MAX-ACCESS  not-accessible
           STATUS  current
           DESCRIPTION
              "An entry in the Local device LAN FX Port Current table."
           INDEX   { rcftChassisIndex,rcftSlotIndex,rcftSlotLANFxPortIndex}
            ::= { rcftSlotLANFxPortCurrentTable 1 }

       RcftSlotLANFxPortCurrentEntry ::=
           SEQUENCE {
           	   rcftSlotLANFxPortIndex				 INTEGER,
               rcftSlotLANFxPortCurrentTemperature	 OCTET STRING,
               rcftSlotLANFxPortCurrentVoltage     	 OCTET STRING,
               rcftSlotLANFxPortCurrentOffsetCurr    OCTET STRING,
               rcftSlotLANFxPortCurrentRecvPower     OCTET STRING,
               rcftSlotLANFxPortCurrentSendPower     OCTET STRING
           }

	    rcftSlotLANFxPortIndex OBJECT-TYPE
	    	SYNTAX INTEGER
	    	MAX-ACCESS read-only
	    	STATUS current
	    	DESCRIPTION
	    	"
	    		LAN Fx port index (1..2)
	    	"
	    	::= { rcftSlotLANFxPortCurrentEntry 1}

        rcftSlotLANFxPortCurrentTemperature OBJECT-TYPE
            SYNTAX  OCTET STRING(SIZE (0..20))
            MAX-ACCESS  read-only
            STATUS  current
            DESCRIPTION
               "this OBJECT indicates the average temperature in the current 15 minute interval."
             ::= { rcftSlotLANFxPortCurrentEntry 2 }

        rcftSlotLANFxPortCurrentVoltage OBJECT-TYPE
            SYNTAX  OCTET STRING(SIZE (0..20))
            MAX-ACCESS  read-only
            STATUS  current
            DESCRIPTION
               "This OBJECT indicates the averaget voltage in the current 15 minute interval."
             ::= { rcftSlotLANFxPortCurrentEntry 3 }

        rcftSlotLANFxPortCurrentOffsetCurr OBJECT-TYPE
            SYNTAX  OCTET STRING(SIZE (0..20))
            MAX-ACCESS  read-only
            STATUS  current
            DESCRIPTION
               "The object indicates the average offset current in the current
               15 minute interval."
            ::= { rcftSlotLANFxPortCurrentEntry 4 }

        rcftSlotLANFxPortCurrentRecvPower OBJECT-TYPE
            SYNTAX  OCTET STRING(SIZE (0..20))
            MAX-ACCESS  read-only
            STATUS  current
            DESCRIPTION
               "This object indicates the average receive power in the current
               15 minute interval."
            ::= { rcftSlotLANFxPortCurrentEntry 5 }

        rcftSlotLANFxPortCurrentSendPower OBJECT-TYPE
            SYNTAX  OCTET STRING(SIZE (0..20))
            MAX-ACCESS  read-only
            STATUS  current
            DESCRIPTION
               "This object indicates the average send power in the current
               15 minute interval."
              ::= { rcftSlotLANFxPortCurrentEntry 6 }

       rcftSlotLANFxPortIntervalTable OBJECT-TYPE
         SYNTAX  SEQUENCE OF RcftSlotLANFxPortIntervalEntry
         MAX-ACCESS  not-accessible
         STATUS  current
         DESCRIPTION
            "The Local device LAN FX Port interval table."
           ::= {rcftSlotStat 7}

       rcftSlotLANFxPortIntervalEntry OBJECT-TYPE
           SYNTAX  RcftSlotLANFxPortIntervalEntry
           MAX-ACCESS  not-accessible
           STATUS  current
           DESCRIPTION
              "An entry in the Local device LAN FX Port interval table."
           INDEX  { rcftChassisIndex,rcftSlotIndex,rcftSlotLANFxPortIndex,rcftSlotLANFxIntervalNumber}
            ::= { rcftSlotLANFxPortIntervalTable 1 }

       RcftSlotLANFxPortIntervalEntry ::=
           SEQUENCE {
           	   rcftSlotLANFxIntervalNumber 			 INTEGER,
               rcftSlotLANFxPortIntervalTemperature	 OCTET STRING,
               rcftSlotLANFxPortIntervalVoltage      OCTET STRING,
               rcftSlotLANFxPortIntervalOffsetCurr   OCTET STRING,
               rcftSlotLANFxPortIntervalRecvPower    OCTET STRING,
               rcftSlotLANFxPortIntervalSendPower    OCTET STRING
           }


	 	rcftSlotLANFxIntervalNumber OBJECT-TYPE
	 		SYNTAX INTEGER
	 		MAX-ACCESS read-only
	 		STATUS current
	 		DESCRIPTION
	 		"
	 			LAN FX PORT 第几个十五分钟
	 		"
	 		::= { rcftSlotLANFxPortIntervalEntry 1 }


        rcftSlotLANFxPortIntervalTemperature OBJECT-TYPE
            SYNTAX  OCTET STRING(SIZE (0..20))
            MAX-ACCESS  read-only
            STATUS  current
            DESCRIPTION
               "this OBJECT indicates the average temperature in the interval 15 minute interval."
             ::= { rcftSlotLANFxPortIntervalEntry 2 }

        rcftSlotLANFxPortIntervalVoltage OBJECT-TYPE
            SYNTAX  OCTET STRING(SIZE (0..20))
            MAX-ACCESS  read-only
            STATUS  current
            DESCRIPTION
               "This OBJECT indicates the averaget voltage in the interval 15 minute interval."
             ::= { rcftSlotLANFxPortIntervalEntry 3 }

        rcftSlotLANFxPortIntervalOffsetCurr OBJECT-TYPE
            SYNTAX  OCTET STRING(SIZE (0..20))
            MAX-ACCESS  read-only
            STATUS  current
            DESCRIPTION
               "The object indicates the average offset interval in the interval
               15 minute interval."
            ::= { rcftSlotLANFxPortIntervalEntry 4 }

        rcftSlotLANFxPortIntervalRecvPower OBJECT-TYPE
            SYNTAX  OCTET STRING(SIZE (0..20))
            MAX-ACCESS  read-only
            STATUS  current
            DESCRIPTION
               "This object indicates the average receive power in the current
               15 minute interval."
            ::= { rcftSlotLANFxPortIntervalEntry 5 }

        rcftSlotLANFxPortIntervalSendPower OBJECT-TYPE
            SYNTAX  OCTET STRING(SIZE (0..20))
            MAX-ACCESS  read-only
            STATUS  current
            DESCRIPTION
               "This object indicates the average send power in the current
               15 minute interval."
            ::= { rcftSlotLANFxPortIntervalEntry 6 }


       rcftSlotWANFxPortTable OBJECT-TYPE
         SYNTAX  SEQUENCE OF RcftSlotWANFxPortEntry
         MAX-ACCESS  not-accessible
         STATUS  current
         DESCRIPTION
            "The Local device WAN FX Port table."
           ::= {rcftSlotStat 8}

       rcftSlotWANFxPortEntry OBJECT-TYPE
           SYNTAX  RcftSlotWANFxPortEntry
           MAX-ACCESS  not-accessible
           STATUS  current
           DESCRIPTION
              "An entry in the Local device WAN FX Port table."
           INDEX   {rcftChassisIndex,rcftSlotIndex,rcftSlotWANFxPortIndex}
            ::= { rcftSlotWANFxPortTable 1 }

       RcftSlotWANFxPortEntry ::=
           SEQUENCE {
               rcftSlotWANFxPortTemperature	  OCTET STRING,
               rcftSlotWANFxPortVoltage       OCTET STRING,
               rcftSlotWANFxPortOffsetCurr    OCTET STRING,
               rcftSlotWANFxPortRecvPower     OCTET STRING,
               rcftSlotWANFxPortSendPower     OCTET STRING
           }

        rcftSlotWANFxPortTemperature OBJECT-TYPE
            SYNTAX  OCTET STRING(SIZE (0..20))
            MAX-ACCESS  read-only
            STATUS  current
            DESCRIPTION
               "this OBJECT indicates the average temperature at present."
             ::= { rcftSlotWANFxPortEntry 1 }

        rcftSlotWANFxPortVoltage OBJECT-TYPE
            SYNTAX  OCTET STRING(SIZE (0..20))
            MAX-ACCESS  read-only
            STATUS  current
            DESCRIPTION
               "This OBJECT indicates the averaget voltage at present."
             ::= { rcftSlotWANFxPortEntry 2 }

        rcftSlotWANFxPortOffsetCurr OBJECT-TYPE
            SYNTAX  OCTET STRING(SIZE (0..20))
            MAX-ACCESS  read-only
            STATUS  current
            DESCRIPTION
               "The object indicates the average offset current at present."
            ::= { rcftSlotWANFxPortEntry 3 }

        rcftSlotWANFxPortRecvPower OBJECT-TYPE
            SYNTAX  OCTET STRING(SIZE (0..20))
            MAX-ACCESS  read-only
            STATUS  current
            DESCRIPTION
               "This object indicates the average receive power at present."
            ::= { rcftSlotWANFxPortEntry 4 }

        rcftSlotWANFxPortSendPower OBJECT-TYPE
            SYNTAX  OCTET STRING(SIZE (0..20))
            MAX-ACCESS  read-only
            STATUS  current
            DESCRIPTION
               "This object indicates the average send power at present."
              ::= { rcftSlotWANFxPortEntry 5 }

      rcftSlotLANFxPortTable OBJECT-TYPE
         SYNTAX  SEQUENCE OF RcftSlotLANFxPortEntry
         MAX-ACCESS  not-accessible
         STATUS  current
         DESCRIPTION
            "The Local device LAN FX Port table."
           ::= {rcftSlotStat 9}

       rcftSlotLANFxPortEntry OBJECT-TYPE
           SYNTAX  RcftSlotLANFxPortEntry
           MAX-ACCESS  not-accessible
           STATUS  current
           DESCRIPTION
              "An entry in the Local device LAN FX Port table."
           INDEX   {rcftChassisIndex,rcftSlotIndex,rcftSlotLANFxPortIndex}
            ::= { rcftSlotLANFxPortTable 1 }

       RcftSlotLANFxPortEntry ::=
           SEQUENCE {
           	   rcftSlotLANFxPortTemperature	  OCTET STRING,
               rcftSlotLANFxPortVoltage       OCTET STRING,
               rcftSlotLANFxPortOffsetCurr    OCTET STRING,
               rcftSlotLANFxPortRecvPower     OCTET STRING,
               rcftSlotLANFxPortSendPower     OCTET STRING
           }


        rcftSlotLANFxPortTemperature OBJECT-TYPE
            SYNTAX  OCTET STRING(SIZE (0..20))
            MAX-ACCESS  read-only
            STATUS  current
            DESCRIPTION
               "this OBJECT indicates the average temperature at present."
             ::= { rcftSlotLANFxPortEntry 1 }

        rcftSlotLANFxPortVoltage OBJECT-TYPE
            SYNTAX  OCTET STRING(SIZE (0..20))
            MAX-ACCESS  read-only
            STATUS  current
            DESCRIPTION
               "This OBJECT indicates the averaget voltage at present."
             ::= { rcftSlotLANFxPortEntry 2 }

        rcftSlotLANFxPortOffsetCurr OBJECT-TYPE
            SYNTAX  OCTET STRING(SIZE (0..20))
            MAX-ACCESS  read-only
            STATUS  current
            DESCRIPTION
               "The object indicates the average offset current at present."
            ::= { rcftSlotLANFxPortEntry 3 }

        rcftSlotLANFxPortRecvPower OBJECT-TYPE
            SYNTAX  OCTET STRING(SIZE (0..20))
            MAX-ACCESS  read-only
            STATUS  current
            DESCRIPTION
               "This object indicates the average receive power at present."
            ::= { rcftSlotLANFxPortEntry 4 }

        rcftSlotLANFxPortSendPower OBJECT-TYPE
            SYNTAX  OCTET STRING(SIZE (0..20))
            MAX-ACCESS  read-only
            STATUS  current
            DESCRIPTION
               "This object indicates the average send power at present."
              ::= { rcftSlotLANFxPortEntry 5 }


 END
