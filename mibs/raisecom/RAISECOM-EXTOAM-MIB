-- MibName=raisecomExtendOam
-- =======================================================================
-- Version info
--
-- Version 1.0 Created 2005.07.27 by LONGYAGN
-- This version of MIB is created just for the use of Network Management Systems
-- display and set the system configuration of convertor .
--
-- Copyright(c) 2002-2005 by RAISECOM TECH, Ltd.
-- =======================================================================



RAISECOM-EXTOAM-MIB DEFINITIONS ::= BEGIN

	IMPORTS
	    EnableVar
			        FROM SWITCH-TC
		raisecomAgent
					FROM RAISECOM-BASE-MIB
		ifIndex
					FROM RFC1213-MIB
		Counter32
					FROM SNMPv2-SMI;

   raisecomExtendOam MODULE-IDENTITY

        LAST-UPDATED    "200507270000Z"
        ORGANIZATION    "Raisecom Science & Technology Co., ltd"
        CONTACT-INFO    "Raisecom Science & Technology Co., ltd.
                         E-mail: support@raisecom.com"

        DESCRIPTION     "Raisecom extend oam Enterprise MIB definition."
        ::= { raisecomAgent 10 }

-- -------------------------------------------------------------------------- --
--	define groups in RAISECOM-EXTOAM-MIB
-- -------------------------------------------------------------------------- --

     raisecomOamExtStatsTable  OBJECT-TYPE
			SYNTAX		SEQUENCE OF	RaisecomOamExtStatsEntry
			MAX-ACCESS	not-accessible
			STATUS		current
			DESCRIPTION
				 "A table of extend OAM statistics."
			::=	{  raisecomExtendOam 1 }

	raisecomOamExtStatsEntry  OBJECT-TYPE
			SYNTAX		RaisecomOamExtStatsEntry
			MAX-ACCESS	not-accessible
			STATUS		current
			DESCRIPTION
			   	"A list of extend OAM statistics parameters."
			INDEX {	ifIndex }
			::=	{ raisecomOamExtStatsTable 1 }

	RaisecomOamExtStatsEntry ::= SEQUENCE {
			raisecomOamExtVariableGetTx       			 Counter32,
			raisecomOamExtVariableGetRx       			 Counter32,
			raisecomOamExtVariableSetTx       			 Counter32,
			raisecomOamExtVariableSetRx       			 Counter32,
			raisecomOamExtVariableGetResponseTx       	 Counter32,
			raisecomOamExtVariableGetResponseRx       	 Counter32,
			raisecomOamExtVariableSetResponseTx       	 Counter32,
			raisecomOamExtVariableSetResponseRx       	 Counter32,
			raisecomOamExtFileReadTx       			     Counter32,
			raisecomOamExtFileReadRx       			     Counter32,
			raisecomOamExtFileWriteTx       			 Counter32,
			raisecomOamExtFileWriteRx       			 Counter32,
			raisecomOamExtFileTransferDataRx       		 Counter32,
			raisecomOamExtFileTransferDataTx       		 Counter32,
			raisecomOamExtFileTransferAckTx       		 Counter32,
			raisecomOamExtFileTransferAckRx       		 Counter32,
			raisecomOamExtNotificationTx       			 Counter32,
			raisecomOamExtNotificationRx       			 Counter32,
			raisecomOamExtStaticInfoTx                   Counter32,
			raisecomOamExtStaticInfoRx                   Counter32,
			raisecomOamExtDynamicInfoTx                  Counter32,
			raisecomOamExtDynamicInfoRx                  Counter32,
			raisecomOamExtConfTx                         Counter32,
			raisecomOamExtConfRx                         Counter32,
			raisecomOamExtCmdTx                          Counter32,
			raisecomOamExtCmdRx                          Counter32,
			raisecomOamExtConnectTx                      Counter32,
			raisecomOamExtConnectRx                      Counter32,
			raisecomOamExtUnknownRx       			     Counter32
			}

     raisecomOamExtVariableGetTx  OBJECT-TYPE
 	      	SYNTAX 	  	Counter32
	      	MAX-ACCESS  read-only
	      	STATUS      current
 	      	DESCRIPTION
           			"A count of the number of extend-OAM variable get
           			 OAMPDUs transmitted on this interface."
          	::= { raisecomOamExtStatsEntry 1 }

     raisecomOamExtVariableGetRx  OBJECT-TYPE
 	      	SYNTAX 	  	Counter32
	      	MAX-ACCESS  read-only
	      	STATUS      current
 	      	DESCRIPTION
           			"A count of the number of extend-OAM variable get
           			 OAMPDUs received on this interface."
          	::= { raisecomOamExtStatsEntry 2 }

     raisecomOamExtVariableSetTx  OBJECT-TYPE
 	      	SYNTAX 	  	Counter32
	      	MAX-ACCESS  read-only
	      	STATUS      current
 	      	DESCRIPTION
           			"A count of the number of extend-OAM variable set
           			 OAMPDUs transmitted on this interface."
          	::= { raisecomOamExtStatsEntry 3 }

     raisecomOamExtVariableSetRx  OBJECT-TYPE
 	      	SYNTAX 	  	Counter32
	      	MAX-ACCESS  read-only
	      	STATUS      current
 	      	DESCRIPTION
           			"A count of the number of extend-OAM variable set
           			 OAMPDUs received on this interface."
          	::= { raisecomOamExtStatsEntry 4 }

     raisecomOamExtVariableGetResponseTx  OBJECT-TYPE
 	      	SYNTAX 	  	Counter32
	      	MAX-ACCESS  read-only
	      	STATUS      current
 	      	DESCRIPTION
           			"A count of the number of extend-OAM variable get
           			responses OAMPDUs transmitted on this interface."
          	::= { raisecomOamExtStatsEntry 5 }

     raisecomOamExtVariableGetResponseRx  OBJECT-TYPE
 	      	SYNTAX 	  	Counter32
	      	MAX-ACCESS  read-only
	      	STATUS      current
 	      	DESCRIPTION
           			"A count of the number of extend-OAM variable get
           			responses OAMPDUs received on this interface."
          	::= { raisecomOamExtStatsEntry 6 }

     raisecomOamExtVariableSetResponseTx  OBJECT-TYPE
 	      	SYNTAX 	  	Counter32
	      	MAX-ACCESS  read-only
	      	STATUS      current
 	      	DESCRIPTION
           			"A count of the number of extend-OAM variable set
           			responses OAMPDUs transmitted on this interface."
          	::= { raisecomOamExtStatsEntry 7 }

     raisecomOamExtVariableSetResponseRx  OBJECT-TYPE
 	      	SYNTAX 	  	Counter32
	      	MAX-ACCESS  read-only
	      	STATUS      current
 	      	DESCRIPTION
           			"A count of the number of extend-OAM variable set
           			responses OAMPDUs received on this interface."
          	::= { raisecomOamExtStatsEntry 8 }

     raisecomOamExtFileReadTx  OBJECT-TYPE
 	      	SYNTAX 	  	Counter32
	      	MAX-ACCESS  read-only
	      	STATUS      current
 	      	DESCRIPTION
           			"A count of the number of extend-OAM file read
           			requests OAMPDUs transmitted on this interface."
          	::= { raisecomOamExtStatsEntry 9 }

     raisecomOamExtFileReadRx  OBJECT-TYPE
 	      	SYNTAX 	  	Counter32
	      	MAX-ACCESS  read-only
	      	STATUS      current
 	      	DESCRIPTION
           			"A count of the number of extend-OAM file read
           			requests OAMPDUs received on this interface."
          	::= { raisecomOamExtStatsEntry 10 }

     raisecomOamExtFileWriteTx  OBJECT-TYPE
 	      	SYNTAX 	  	Counter32
	      	MAX-ACCESS  read-only
	      	STATUS      current
 	      	DESCRIPTION
           			"A count of the number of extend-OAM file write
           			requests OAMPDUs transmitted on this interface."
          	::= { raisecomOamExtStatsEntry 11 }

    raisecomOamExtFileWriteRx  OBJECT-TYPE
 	      	SYNTAX 	  	Counter32
	      	MAX-ACCESS  read-only
	      	STATUS      current
 	      	DESCRIPTION
           			"A count of the number of extend-OAM file write
           			requests OAMPDUs received on this interface."
          	::= { raisecomOamExtStatsEntry 12 }

    raisecomOamExtFileTransferDataRx  OBJECT-TYPE
 	      	SYNTAX 	  	Counter32
	      	MAX-ACCESS  read-only
	      	STATUS      current
 	      	DESCRIPTION
           			"A count of the number of extend-OAM file transfer
           			data OAMPDUs received on this interface."
          	::= { raisecomOamExtStatsEntry 13 }

    raisecomOamExtFileTransferDataTx  OBJECT-TYPE
 	      	SYNTAX 	  	Counter32
	      	MAX-ACCESS  read-only
	      	STATUS      current
 	      	DESCRIPTION
           			"A count of the number of extend-OAM file transfer
           			data OAMPDUs transmitted on this interface."
          	::= { raisecomOamExtStatsEntry 14 }

    raisecomOamExtFileTransferAckTx  OBJECT-TYPE
 	      	SYNTAX 	  	Counter32
	      	MAX-ACCESS  read-only
	      	STATUS      current
 	      	DESCRIPTION
           			"A count of the number of extend-OAM file transfer
           			acks OAMPDUs transmitted on this interface."
          	::= { raisecomOamExtStatsEntry 15 }

    raisecomOamExtFileTransferAckRx  OBJECT-TYPE
 	      	SYNTAX 	  	Counter32
	      	MAX-ACCESS  read-only
	      	STATUS      current
 	      	DESCRIPTION
           			"A count of the number of extend-OAM file transfer
           			acks OAMPDUs received on this interface."
          	::= { raisecomOamExtStatsEntry 16 }

    raisecomOamExtNotificationTx  OBJECT-TYPE
 	      	SYNTAX 	  	Counter32
	      	MAX-ACCESS  read-only
	      	STATUS      current
 	      	DESCRIPTION
           			"A count of the number of extend-OAM notifications
           			 OAMPDUs transmitted on this interface."
          	::= { raisecomOamExtStatsEntry 17 }

    raisecomOamExtNotificationRx  OBJECT-TYPE
 	      	SYNTAX 	  	Counter32
	      	MAX-ACCESS  read-only
	      	STATUS      current
 	      	DESCRIPTION
           			"A count of the number of extend-OAM notifications
           			 OAMPDUs received on this interface."
          	::= { raisecomOamExtStatsEntry 18 }

    raisecomOamExtStaticInfoTx  OBJECT-TYPE
 	      	SYNTAX 	  	Counter32
	      	MAX-ACCESS  read-only
	      	STATUS      current
 	      	DESCRIPTION
           			"A count of the number of static infomation
           			 OAMPDUs transmitted on this interface."
          	::= { raisecomOamExtStatsEntry 19 }

    raisecomOamExtStaticInfoRx  OBJECT-TYPE
 	      	SYNTAX 	  	Counter32
	      	MAX-ACCESS  read-only
	      	STATUS      current
 	      	DESCRIPTION
           			"A count of the number of static infomation
           			 OAMPDUs received on this interface."
          	::= { raisecomOamExtStatsEntry 20 }

    raisecomOamExtDynamicInfoTx  OBJECT-TYPE
 	      	SYNTAX 	  	Counter32
	      	MAX-ACCESS  read-only
	      	STATUS      current
 	      	DESCRIPTION
           			"A count of the number of dynamic infomation
           			 OAMPDUs transmitted on this interface."
          	::= { raisecomOamExtStatsEntry 21 }

    raisecomOamExtDynamicInfoRx  OBJECT-TYPE
 	      	SYNTAX 	  	Counter32
	      	MAX-ACCESS  read-only
	      	STATUS      current
 	      	DESCRIPTION
           			"A count of the number of dynamic infomation
           			 OAMPDUs received on this interface."
          	::= { raisecomOamExtStatsEntry 22 }

    raisecomOamExtConfTx  OBJECT-TYPE
 	      	SYNTAX 	  	Counter32
	      	MAX-ACCESS  read-only
	      	STATUS      current
 	      	DESCRIPTION
           			"A count of the number of configuration infomation
           			 OAMPDUs transmitted on this interface."
          	::= { raisecomOamExtStatsEntry 23 }

    raisecomOamExtConfRx  OBJECT-TYPE
 	      	SYNTAX 	  	Counter32
	      	MAX-ACCESS  read-only
	      	STATUS      current
 	      	DESCRIPTION
           			"A count of the number of configuration infomation
           			 OAMPDUs received on this interface."
          	::= { raisecomOamExtStatsEntry 24 }

    raisecomOamExtCmdTx  OBJECT-TYPE
 	      	SYNTAX 	  	Counter32
	      	MAX-ACCESS  read-only
	      	STATUS      current
 	      	DESCRIPTION
           			"A count of the number of command infomation
           			 OAMPDUs transmitted on this interface."
          	::= { raisecomOamExtStatsEntry 25 }

    raisecomOamExtCmdRx  OBJECT-TYPE
 	      	SYNTAX 	  	Counter32
	      	MAX-ACCESS  read-only
	      	STATUS      current
 	      	DESCRIPTION
           			"A count of the number of command infomation
           			 OAMPDUs received on this interface."
          	::= { raisecomOamExtStatsEntry 26 }

    raisecomOamExtConnectTx  OBJECT-TYPE
 	      	SYNTAX 	  	Counter32
	      	MAX-ACCESS  read-only
	      	STATUS      current
 	      	DESCRIPTION
           			"A count of the number of connect infomation
           			 OAMPDUs transmitted on this interface."
          	::= { raisecomOamExtStatsEntry 27 }

    raisecomOamExtConnectRx  OBJECT-TYPE
 	      	SYNTAX 	  	Counter32
	      	MAX-ACCESS  read-only
	      	STATUS      current
 	      	DESCRIPTION
           			"A count of the number of connect infomation
           			 OAMPDUs received on this interface."
          	::= { raisecomOamExtStatsEntry 28 }

     raisecomOamExtUnknownRx  OBJECT-TYPE
 	      	SYNTAX 	  	Counter32
	      	MAX-ACCESS  read-only
	      	STATUS      current
 	      	DESCRIPTION
           			"The total number of unknown extend-OAM packets
           			received on this interface."
          	::= { raisecomOamExtStatsEntry 29 }



     raisecomOamExtStatusTable  OBJECT-TYPE
			SYNTAX		SEQUENCE OF	RaisecomOamExtStatusEntry
			MAX-ACCESS	not-accessible
			STATUS		current
			DESCRIPTION
				 "A table of extended OAM status."
			::=	{  raisecomExtendOam 2 }

	raisecomOamExtStatusEntry  OBJECT-TYPE
			SYNTAX		RaisecomOamExtStatusEntry
			MAX-ACCESS	not-accessible
			STATUS		current
			DESCRIPTION
			   	"A list of extend OAM status parameters."
			INDEX {	ifIndex }
			::=	{ raisecomOamExtStatusTable 1 }

 	RaisecomOamExtStatusEntry ::= SEQUENCE {
			raisecomOamExtStatus       			 INTEGER
			}

    raisecomOamExtStatus   OBJECT-TYPE
  	        SYNTAX  INTEGER
 	        {
 	           nonoperative(1),
               invariableInfoGet(2),
               invariableInfoGetError(3),
               operational(4),
               fileTransfer(5)
            }
         	MAX-ACCESS 	read-only
        	STATUS 		current
        	DESCRIPTION
                	"Extend-OAM status."
         	::= { raisecomOamExtStatusEntry 1 }

-- raisecomOamExtRemoteMibObjects
    raisecomOamExtRemoteMibObjects OBJECT IDENTIFIER ::= { raisecomExtendOam 3 }

	raisecomOamNotificationEnable OBJECT-TYPE
		    SYNTAX  EnableVar
		    ACCESS read-write
		    STATUS current
		    DESCRIPTION
		        "Specifies whether or not send OAM notification to local."
		    ::= {  raisecomOamExtRemoteMibObjects 1 }

    raisecomOamExtConfigReqEnable OBJECT-TYPE
		    SYNTAX  EnableVar
		    ACCESS read-write
		    STATUS current
		    DESCRIPTION
		        "Enable or disable configuration request function."
		    ::= {  raisecomOamExtRemoteMibObjects 2 }
END
