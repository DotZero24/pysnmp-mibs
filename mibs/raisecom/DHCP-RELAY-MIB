--MibName=rcDhcpRelay
-- *****************************************************************
-- switch-dhcprelay-mib.smi:  Raisecom DHCP Relay MIB file
--
-- Apr 2007, wumingyu
--
-- Copyright (c) 1999-2007 by Raisecom Technology Co., Ltd.
-- All rights reserved.
--
-- *****************************************************************

DHCP-RELAY-MIB DEFINITIONS ::= BEGIN

    IMPORTS
        MODULE-IDENTITY, TimeTicks, OBJECT-TYPE
             FROM SNMPv2-SMI
        RowStatus                   FROM SNMPv2-TC
        EnableVar,Vlanset			FROM SWITCH-TC
        iscomSwitch  FROM RAISECOM-BASE-MIB;

    rcDhcpRelay MODULE-IDENTITY
          LAST-UPDATED "200412200000Z"  -- Dec 20, 2004
          ORGANIZATION "raisecom."
          CONTACT-INFO
              "raisecom
                  E-mail: "

          DESCRIPTION "dhcp module management."

          REVISION    "200412200000Z"  -- Dec 20, 2004
          DESCRIPTION "Initial Version"

          ::= { iscomSwitch 13 }

    rcDhcpRelayMibObjects	OBJECT IDENTIFIER ::= { rcDhcpRelay 1 }
    rcDhcpRelayGroup      	OBJECT IDENTIFIER ::= { rcDhcpRelayMibObjects 1 }
    rcDhcpRelayStatistics  OBJECT IDENTIFIER ::= { rcDhcpRelayMibObjects 2 }


--------------dhcp relay group--------------------

          rcDhcpRelayEnable OBJECT-TYPE
              SYNTAX  EnableVar
              MAX-ACCESS  read-write
              STATUS  current
              DESCRIPTION
                      "The enabled/disabled status of the dhcps relay."
              DEFVAL { disabled }
              ::= { rcDhcpRelayGroup 1 }

    	rcDhcpRelayStartTime  OBJECT-TYPE
      	  	SYNTAX TimeTicks
      	  	MAX-ACCESS read-only
     	   	STATUS mandatory
       	 	DESCRIPTION
            	"This read-only object displays the DHCP Relay startup time."
        	::= { rcDhcpRelayGroup 2 }


------------------dhcp relay server table----------------
          rcDhcpRelayServerTable OBJECT-TYPE
              SYNTAX  SEQUENCE OF RcDhcpRelayServerEntry
              MAX-ACCESS  not-accessible
              STATUS  current
              DESCRIPTION
                      "A table that contains target server information
                      for the DHCP Relay."
              ::= { rcDhcpRelayGroup 3 }

          rcDhcpRelayServerEntry OBJECT-TYPE
              SYNTAX  RcDhcpRelayServerEntry
              MAX-ACCESS  not-accessible
              STATUS  current
              DESCRIPTION
                      "A entry that contains target server information
                      for the DHCP Relay."
              INDEX   { rcDhcpRelayServerIndex }
              ::= { rcDhcpRelayServerTable 1 }

          RcDhcpRelayServerEntry ::=
              SEQUENCE {
                  rcDhcpRelayServerIndex  INTEGER,
                  rcDhcpRelayServerAddress IpAddress,
                  rcDhcpRelayServerRowStatus RowStatus
                  }

          rcDhcpRelayServerIndex OBJECT-TYPE
              SYNTAX  INTEGER
              MAX-ACCESS  not-accessible
              STATUS  current
              DESCRIPTION
                      "index of target server."
              REFERENCE
                      "SOUCE-CODE OF DHCP SERVER"
              ::= { rcDhcpRelayServerEntry 1 }

          rcDhcpRelayServerAddress OBJECT-TYPE
              SYNTAX  IpAddress
              MAX-ACCESS  read-create
              STATUS  current
              DESCRIPTION
                      "the ip address of target server."
              REFERENCE
                      "SOUCE-CODE OF DHCP SERVER"
              ::= { rcDhcpRelayServerEntry 2 }

          rcDhcpRelayServerRowStatus OBJECT-TYPE
              SYNTAX  RowStatus
              MAX-ACCESS  read-create
              STATUS  current
              DESCRIPTION
                      "DURABLE:
                      the rows tatus of target server address table."
              REFERENCE
                      "SOUCE-CODE OF DHCP SERVER."
              ::= { rcDhcpRelayServerEntry 3 }


--other scalars--
          rcDhcpRelayServerNextIndex OBJECT-TYPE
              SYNTAX  INTEGER (1..8)
              MAX-ACCESS  read-only
              STATUS  current
              DESCRIPTION
                      "The next index of Target server."
              REFERENCE
                      "DHCP SERVER SOUCE-CODE"
              ::= { rcDhcpRelayGroup 4 }


          rcDhcpRelayVlans OBJECT-TYPE
              SYNTAX  Vlanset
              MAX-ACCESS  read-write
              STATUS  current
              DESCRIPTION
                      "The enabled/disabled  status of dhcp-relay of vlan."
              REFERENCE
                      "DHCP SERVER SOUCE-CODE"
              ::= { rcDhcpRelayGroup 5 }

--dhcp Relay statistics--
    rcDhcpRelayStatsBootps  OBJECT-TYPE
        SYNTAX Counter
        MAX-ACCESS read-only
        STATUS mandatory
        DESCRIPTION
            "This read-only object displays the DHCP Relay receive the Bootps num."
        ::= {rcDhcpRelayStatistics 1 }

    rcDhcpRelayStatsDiscovers  OBJECT-TYPE
        SYNTAX Counter
        MAX-ACCESS read-only
        STATUS mandatory
        DESCRIPTION
            "This read-only object displays the DHCP Relay receive the Discovers num."
        ::= { rcDhcpRelayStatistics 2 }

    rcDhcpRelayStatsRequests  OBJECT-TYPE
        SYNTAX Counter
        MAX-ACCESS read-only
        STATUS mandatory
        DESCRIPTION
            "This read-only object displays the DHCP Relay receive the Requests num."
        ::= { rcDhcpRelayStatistics 3 }

    rcDhcpRelayStatsReleases  OBJECT-TYPE
        SYNTAX Counter
        MAX-ACCESS read-only
        STATUS mandatory
        DESCRIPTION
            "This read-only object displays the DHCP Relay receive the Releases num."
        ::= { rcDhcpRelayStatistics 4 }

    rcDhcpRelayStatsOffers  OBJECT-TYPE
        SYNTAX Counter
        MAX-ACCESS read-only
        STATUS mandatory
        DESCRIPTION
            "This read-only object displays the DHCP Relay receive the Offers num."
        ::= { rcDhcpRelayStatistics 5 }

    rcDhcpRelayStatsAcks  OBJECT-TYPE
        SYNTAX Counter
        MAX-ACCESS read-only
        STATUS mandatory
        DESCRIPTION
            "This read-only object displays the DHCP Relay receive the Acks num."
        ::= { rcDhcpRelayStatistics 6 }

    rcDhcpRelayStatsNacks  OBJECT-TYPE
        SYNTAX Counter
        MAX-ACCESS read-only
        STATUS mandatory
        DESCRIPTION
            "This read-only object displays the DHCP Relay receive the Nacks num."
        ::= { rcDhcpRelayStatistics 7 }

    rcDhcpRelayStatsDeclines  OBJECT-TYPE
        SYNTAX Counter
        MAX-ACCESS read-only
        STATUS mandatory
        DESCRIPTION
            "This read-only object displays the DHCP Relay receive the Declines num."
        ::= {rcDhcpRelayStatistics 8 }

    rcDhcpRelayStatsInformations  OBJECT-TYPE
        SYNTAX Counter
        MAX-ACCESS read-only
        STATUS mandatory
        DESCRIPTION
            "This read-only object displays the DHCP Relay receive the Informations num."
        ::= {rcDhcpRelayStatistics 9 }

    rcDhcpRelayStatsUnknows  OBJECT-TYPE
        SYNTAX Counter
        MAX-ACCESS read-only
        STATUS mandatory
        DESCRIPTION
            "This read-only object displays the DHCP Relay receive the unknowed packets num."
        ::= {rcDhcpRelayStatistics 10 }

    rcDhcpRelayStatsPackets  OBJECT-TYPE
        SYNTAX Counter
        MAX-ACCESS read-only
        STATUS mandatory
        DESCRIPTION
            "This read-only object displays the DHCP Relay receive the total packets num."
        ::= {rcDhcpRelayStatistics 11 }

END
