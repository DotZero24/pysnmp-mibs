-- *****************************************************************
-- RaisecomMib_Advent.my:  RC002 MIB
--
-- Copyright (c) 2001 by raisecom Systems, Inc.
-- All rights reserved.
--
-- sunsuli@raisecom.com: 04-Oct-20
-- *****************************************************************


   RAISECOM-RCFT-MIB DEFINITIONS ::= BEGIN

    IMPORTS
      MODULE-IDENTITY,  NOTIFICATION-TYPE,Counter32, Gauge32, OBJECT-TYPE, enterprises,TimeTicks
                 FROM SNMPv2-SMI
      IpAddress,mib-2,Unsigned32 FROM SNMPv2-SMI
      TRAP-TYPE  FROM RFC-1215
      DisplayString,    TimeStamp
                 FROM SNMPv2-TC
      MODULE-COMPLIANCE, OBJECT-GROUP
                 FROM SNMPv2-CONF;

    raiseCom MODULE-IDENTITY
       LAST-UPDATED "1010221638Z"
       ORGANIZATION "RaiseCom Technology Co., Ltd."
       CONTACT-INFO
       "
                        Tel: +86-10-8288-4499
                        Fax: +86-10-8288-8500
                     E-mail: raisecom@xinmail.cn "
       DESCRIPTION
             " The MIB module for RaiseCom RC Fiber Transceiver."
       REVISION "0307280000Z"
       DESCRIPTION
             " "
       REVISION      "0901090000Z"
       DESCRIPTION
              "
                rcftSlotOpticalDeviceStatus add defination for BIT8-BIT4;
                add node:rcftSlotApsWaitToRestore;
                add trap:rcftSlotSPChannelTrap,	rcftSlotPSChannelTrap;
				--by sunying"
       REVISION      "0903240000Z"
       DESCRIPTION
              "
                add node:rcftSlotApsE6SwitchDelay,rcftSlotApsE3SwitchDelay
				--by sunying"
	   REVISION      "0905190000Z"
       DESCRIPTION
              "
                opticalModuleType 和 remoteopticalModuleType 中取消了ss3(9) 光头类型
                采用公司统一的光头类型(即ss34(9) 、ss35(10))
				--by kuanglili"
	   REVISION      "0905260000Z"
	   DESCRIPTION
              "
                添加RC906G-FE/X-4E1-MASTER/SLAVE、RC906-FE/X-E1-MASTER/SLAVE设备类型
				--by kuanglili"
	   REVISION    "200906040000Z"
	   DESCRIPTION
	   		"
	   		 将一级远端RC522-FE-REV-C的类型号改为11030
	   		   一级远端RC522-FE-REV-C的类型号改为11029
	   		 			   ---by kuanglili
	   		"
	   REVISION    "200906090000Z"
	   DESCRIPTION
	   		"
	   		  rcftSlotFrameLength节点添加9KB和2048B两个枚举值。
			   ---by kuanglili
	   		"
 	   REVISION    "200908280000Z"
	   DESCRIPTION
	   		"
	   		  1、rcftSlotCLKMode 增加枚举值	7：透传  Transparent；
	   		  2、把接口级属性改为设备级属性 rcftE1DS1PortType；
	   		  3、添加节点rcftSlotManageID、rcftSlotE1PortNumber
			   ---by wuyanxiong
	   		"
	  REVISION      "0909031130Z"
     DESCRIPTION
              "
       add device type:
               rcftTypeRC521H-FE-DoubleFiber-S(20071),   --双纤台式
               rcftTypeRC521H-FE-SingleFiber-S(20072),   --单纤台式
				--by xujingru
              "
        REVISION      "0909091130Z"
     DESCRIPTION
              "
       add device type:
               rcftTypeRCMS2802-60FX-REV-A(13084),
				--by kuanglili
              "
       REVISION      "090910300943Z"
     DESCRIPTION
              "
       			add device type:
               			rcftSlotQoS,
							--by kuanglili
              "
        REVISION      "1001271123Z"
     DESCRIPTION
              "
       			add device type:
       					rcftSlotTPIDRemark
               			rcftRSlotTPIDRemark,
							--by kuanglili
              "
        REVISION      "1003030000Z"
     DESCRIPTION
              "
       			add device type:
       					rcftSlotDeviceMibUse
							--by wuyanxiong
              "
	  REVISION      "1003100000Z"
     DESCRIPTION
              "
       add device type:
            rcftTypeRC552-FE-REV-B-MASTER(10201),
            rcftTypeRC552-FE-REV-B-SLAVE(10203),
				--by wuyanxiong
              "
        REVISION      "1003100000Z"
     DESCRIPTION
              "
       			修改rcftSlotDeviceMibUse枚举值，从1开始
       			{
		      		mib002(1),
		      		rccomlib(2)
	      		}
							--by wuyanxiong
              "

        REVISION      "1005131632Z"
     DESCRIPTION
              "
       			增加cwdmClientWorkSpeed枚举值
       			{
		      	speed2fc(8),
				speedfc(9)
				bypass (10)
				stm16+fec(11)
	      		}
							--by kuanglili
              "
        REVISION      "1007020000Z"
     DESCRIPTION
              "
	       		add device type:
	            rcftTypeRC602E-GE-MASTER(11031),		--RC602E-E 虚拟设备类型
	            rcftTypeRC602E-GE-SLAVE(11032),
	            rcftTypeRC602E-GE(11033),
					--by wuyanxiong
              "

        REVISION      "1010221638Z"
     DESCRIPTION
              "
       			增加rcftSlotConfStatTable配置表,用于配置和配置显示
       			下挂rcftSlotConfStatEntry入口,内含四个结点
       			{
        			rcftSlotConfEDuplex
			        rcftSlotConfESpeed
			        rcftRSlotConfEDuplex
			        rcftRSlotConfESpeed
			        rcftConfTxWorkStatus
	    		}
							--by yangbintao
              "
        REVISION      "1011150000Z"
     DESCRIPTION
              "
	       		1、add device type:
		            rcftTypeRCMS2902-120LFE-MASTER(62587),   ---对应设备类型0xF47B
		            rcftTypeRCMS2902-120LFE-SLAVE(62588),    ---对应设备类型0xF47C
		            rcftTypeRCMS2902-240LFE-MASTER(62590),   ---对应设备类型0xF47E
		            rcftTypeRCMS2902-240LFE-SLAVE(62591),    ---对应设备类型0xF47F
		            rcftTypeRCMS2902-60FE-MASTER(62593),	 ---对应设备类型0xF481
		            rcftTypeRCMS2902-60FE-SLAVE(62594),      ---对应设备类型0xF482
		            rcftTypeRC862-60-MASTER(62596),   		 ---对应设备类型0xF484
		            rcftTypeRC862-60-SLAVE(62597),    		 ---对应设备类型0xF485
		            rcftTypeRC862-30-MASTER(62601),   		 ---对应设备类型0xF489
		            rcftTypeRC862-30-SLAVE(62602),    		 ---对应设备类型0xF48A

		            rcftTypeRCMS2912-480FE-MASTER(62609),   ---对应设备类型0xF491
		            rcftTypeRCMS2912-480FE-SLAVE(62610),    ---对应设备类型0xF492
		            rcftTypeRCMS2912-240FE-MASTER(62612),   ---对应设备类型0xF494
		            rcftTypeRCMS2912-240FE-SLAVE(62613),    ---对应设备类型0xF495

		        2、修改设备名称RCMS2912-8/4T1E1GE 改为 RCMS2912-8/4E1T1GE

					--by wuyanxiong
              "

          REVISION      "1208100000Z"
       DESCRIPTION
              "
                add node:rcftSlotApsSwitchDelay
				    --by wangjunduo
	     "
	 REVISION      "1305080000Z"
      DESCRIPTION
            "
                opticalModuleType 和 remoteopticalModuleType 增加了
                SFP光头类型(即optical-sfp(15))
				--by wangjunduo
	   "

              ::= { enterprises 8886 }

   rc002 OBJECT IDENTIFIER ::= { raiseCom 2 }

    rcftMibObjects OBJECT IDENTIFIER ::= { rc002 1 }

    rcftTraps OBJECT IDENTIFIER ::= { rc002 0 }

--
--	THIS TABLE DEFINE YOUR PRIVATE MIB INFORMATION
--


    rcftSystem OBJECT IDENTIFIER ::= { rcftMibObjects 1 }

    rcftChassis OBJECT IDENTIFIER ::= { rcftMibObjects 2 }

    rcftPower  OBJECT IDENTIFIER ::= { rcftMibObjects 3 }

    rcftFan    OBJECT IDENTIFIER ::= { rcftMibObjects 4 }

    rcftSlotStat OBJECT IDENTIFIER ::= { rcftMibObjects 5 }

    rcftSysTrapTarget OBJECT IDENTIFIER ::= { rcftSystem 7}

    rcftSysTrapTargetEntry OBJECT IDENTIFIER ::= { rcftSysTrapTarget 1}

    rcftSysTrapPort OBJECT IDENTIFIER ::= { rcftSystem 9}

    rcftSysTrapPortEntry OBJECT IDENTIFIER ::= { rcftSysTrapPort 1}


    rcftSysId OBJECT-TYPE
        SYNTAX INTEGER
        MAX-ACCESS read-write
        STATUS current
        DESCRIPTION
        "
          设备编号
          Device ID
        "
        ::= {rcftSystem 1}

    rcftSysLevel OBJECT-TYPE
        SYNTAX INTEGER
        {
            kernal(1),
            convergence(2),
            subordinate(3)
        }
        MAX-ACCESS read-write
        STATUS current
        DESCRIPTION
        "
          描述系统的级别. 1:核心,2:汇接,3:次要

        "
        ::= {rcftSystem 2}

    rcftSysChassisNum OBJECT-TYPE
        SYNTAX INTEGER
        MAX-ACCESS read-only
        STATUS current
        DESCRIPTION
        "
          实际在位的机箱数量
        "
        ::= {rcftSystem 3}

    rcftSysAlarm OBJECT-TYPE
        SYNTAX INTEGER
        {
            normal(1),
            minor(2),
            serious(3)
        }
        MAX-ACCESS read-only
        STATUS current
        DESCRIPTION
          " 1:正常,2:轻微告警,包括风扇故障.LINK闪烁
            3:严重告警,包括机箱温度过热.电源故障.背板监控失效"
        ::= {rcftSystem 4}

    rcftSysTmptAlarmThreshold OBJECT-TYPE
        SYNTAX INTEGER
        MAX-ACCESS read-write
        STATUS current
        DESCRIPTION
        "
           机箱温度告警阈值.
           The object is the temperature threshold of the chassis.
           When the chassis temperature is higer than the value of this object
           a notification will be sent.
        "
        ::= {rcftSystem 5}

    rcftSysTrapEnable OBJECT-TYPE
        SYNTAX INTEGER
        {
            enable(1),
            disable(2)
        }
        MAX-ACCESS read-write
        STATUS current
        DESCRIPTION
        "
          告警使能.
          This object controls if the generation of
	   notifications is enabled. If the value of this object
	   is 'enable(1)', then all notifications are enabled; otherwise they are disabled.
        "
        ::= {rcftSystem 6}

    rcftTrapSink1 OBJECT-TYPE
        SYNTAX IpAddress
        MAX-ACCESS  read-write
        STATUS current
        DESCRIPTION
          "
           接收告警的第一个服务器的IP地址.
           The value of this object is the first Ip Address of the first server to which
 	       the notification will be sent.
		 "
          ::={rcftSysTrapTargetEntry 1}

    rcftTrapSink2 OBJECT-TYPE
        SYNTAX IpAddress
        MAX-ACCESS  read-write
        STATUS current
        DESCRIPTION
        "
           接收告警的第二个服务器的IP地址.
          The value of this object is the Ip Address of the second server to which
 	      the notification will be sent.
        "
          ::={rcftSysTrapTargetEntry 2}

    rcftTrapSink3 OBJECT-TYPE
        SYNTAX IpAddress
        MAX-ACCESS  read-write
        STATUS current
        DESCRIPTION
        "
          接收告警的第三个服务器的IP地址.
          The value of this object is the Ip Address of the 3rd server to which
 	      the notification will be sent.
        "
          ::={rcftSysTrapTargetEntry 3}

    rcftTrapSink4 OBJECT-TYPE
        SYNTAX IpAddress
        MAX-ACCESS  read-write
        STATUS current
        DESCRIPTION
        "
          接收告警的第四个服务器的IP地址.
          The value of this object is the Ip Address of the 4th server to which
 	      the notification will be sent.
	"
         ::={rcftSysTrapTargetEntry 4}

    rcftTrapSink5 OBJECT-TYPE
        SYNTAX IpAddress
        MAX-ACCESS  read-write
        STATUS current
        DESCRIPTION
        "
          接收告警的第五个服务器的IP地址.
          The value of this object is the Ip Address of the 5th server to which
 	      the notification will be sent.
        "
         ::={rcftSysTrapTargetEntry 5}

    rcftTrapSink6 OBJECT-TYPE
        SYNTAX IpAddress
        MAX-ACCESS  read-write
        STATUS current
        DESCRIPTION
        "
          接收告警的第六个服务器的IP地址.
          The value of this object is the Ip Address of the 6th server to which
 	      the notification will be sent.
        "
         ::={rcftSysTrapTargetEntry 6}

    rcftTrapSink7 OBJECT-TYPE
        SYNTAX IpAddress
        MAX-ACCESS  read-write
        STATUS current
        DESCRIPTION
        "
          接收告警的第七个服务器的IP地址.
          The value of this object is the Ip Address of the 7th server to which
 	      the notification will be sent.
        "
         ::={rcftSysTrapTargetEntry 7}

    rcftTrapSink8 OBJECT-TYPE
        SYNTAX IpAddress
        MAX-ACCESS  read-write
        STATUS current
        DESCRIPTION
        "
         接收告警的第八个服务器的IP地址.
         The value of this object is the Ip Address of the 8th server to which
 	     the notification will be sent.
        "
         ::={rcftSysTrapTargetEntry 8}

    rcftRSlotTmptAlarmThreshold OBJECT-TYPE
        SYNTAX INTEGER
        MAX-ACCESS read-write
        STATUS current
        DESCRIPTION
          "
            远端机箱温度告警阈值.
          "
        ::= {rcftSystem 8}


    rcftTrapPort1 OBJECT-TYPE
        SYNTAX INTEGER
        MAX-ACCESS  read-write
        STATUS current
        DESCRIPTION
        "
          接收告警的第一个服务器的端口号.
          The value of this object is the first port of the first server to which
 	      the notification will be sent.
        "
          ::={rcftSysTrapPortEntry 1}

    rcftTrapPort2 OBJECT-TYPE
        SYNTAX INTEGER
        MAX-ACCESS  read-write
        STATUS current
        DESCRIPTION
        "
          接收告警的第二个服务器的端口号.
          The value of this object is the port of the first server to which
 	      the notification will be sent.
        "
          ::={rcftSysTrapPortEntry 2}

    rcftTrapPort3 OBJECT-TYPE
        SYNTAX INTEGER
        MAX-ACCESS  read-write
        STATUS current
        DESCRIPTION
        "
          接收告警的第三个服务器的端口号.
          The value of this object is the port of the second server to which
 	      the notification will be sent.
        "
          ::={rcftSysTrapPortEntry 3}

    rcftTrapPort4 OBJECT-TYPE
        SYNTAX INTEGER
        MAX-ACCESS  read-write
        STATUS current
        DESCRIPTION
        "
          接收告警的第四个服务器的端口号.
          The value of this object is the port of the third server to which
 	      the notification will be sent.
        "
          ::={rcftSysTrapPortEntry 4}

    rcftTrapPort5 OBJECT-TYPE
        SYNTAX INTEGER
        MAX-ACCESS  read-write
        STATUS current
        DESCRIPTION
        "
          接收告警的第五个服务器的端口号.
          The value of this object is the port of the 4th server to which
 	      the notification will be sent.
        "
          ::={rcftSysTrapPortEntry 5}

    rcftTrapPort6 OBJECT-TYPE
        SYNTAX INTEGER
        MAX-ACCESS  read-write
        STATUS current
        DESCRIPTION
        "
          接收告警的第六个服务器的端口号.
          The value of this object is the port of the 5th server to which
 	      the notification will be sent.
        "
          ::={rcftSysTrapPortEntry 6}

    rcftTrapPort7 OBJECT-TYPE
        SYNTAX INTEGER
        MAX-ACCESS  read-write
        STATUS current
        DESCRIPTION
        "
         接收告警的第七个服务器的端口号.
         The value of this object is the port of the 6th server to which
 	     the notification will be sent.
        "
          ::={rcftSysTrapPortEntry 7}

    rcftTrapPort8 OBJECT-TYPE
        SYNTAX INTEGER
        MAX-ACCESS  read-write
        STATUS current
        DESCRIPTION
        "
          接收告警的第八个服务器的端口号.
          The value of this object is the port of the 7th server to which
 	      the notification will be sent.
        "
          ::={rcftSysTrapPortEntry 8}


    rcftChassisTable OBJECT-TYPE
        SYNTAX SEQUENCE OF RcftChassisEntry
        MAX-ACCESS not-accessible
        STATUS current
        DESCRIPTION
        "
          机箱表.
          The table holding information related to the chasiss status.
        "
        ::= {rcftChassis 1}

    rcftChassisEntry OBJECT-TYPE
        SYNTAX RcftChassisEntry
        MAX-ACCESS not-accessible
        STATUS current
        DESCRIPTION
        "
          The chassis information entry.
        "
        INDEX { rcftChassisIndex }
        ::= {rcftChassisTable 1}

    RcftChassisEntry ::= SEQUENCE {
        rcftChassisIndex
            INTEGER,
        rcftChassisExist
            INTEGER,
        rcftChassisTmpt
            INTEGER,
        rcftPowerNum
            INTEGER,
        rcftChassisType
            INTEGER,
        rcftChassisDescr
           DisplayString
    }

    rcftChassisIndex  OBJECT-TYPE
        SYNTAX INTEGER
        MAX-ACCESS read-only
        STATUS current
        DESCRIPTION
        "
          机箱索引(1-4)
          Chassis index ranging between 1 and 4.
        "
        ::= {rcftChassisEntry 1}

    rcftChassisExist OBJECT-TYPE
        SYNTAX INTEGER
        {
            exist(1),
            notExist(2)
        }
        MAX-ACCESS read-only
        STATUS current
        DESCRIPTION
        "
          机箱是否存在标志. 当该标志是notExist(2)不存在时,该机箱的其他状态:
          rcftChassisTmpt.cftPowerNum.rcftChassisType的值为0,没有意义.
          The value of this object indicates whether the chassis is exist or not.
          Note that when the chassis is not exist the value of the objects such as
          rcftChassisTmpt, rcftPowerNum and rcftChassisType is 0 which means meaningless.

        "
        ::= {rcftChassisEntry 2}

    rcftChassisTmpt OBJECT-TYPE
        SYNTAX INTEGER
        MAX-ACCESS read-only
        STATUS current
        DESCRIPTION
        "
          机箱温度,单位为摄氏度.
          Chassis temperature which unit is centigrade.
        "
        ::= {rcftChassisEntry 3}

    rcftPowerNum OBJECT-TYPE
        SYNTAX INTEGER
        MAX-ACCESS read-only
        STATUS current
        DESCRIPTION
        "
          机箱电源数量.
        "
        ::= {rcftChassisEntry 4}

    rcftChassisType OBJECT-TYPE
        SYNTAX INTEGER
        {
           rcChassis16BP-REV-C(1),
           rcChassis16BP-REV-D(2),
           rcChassis4BP-REV-A(3),
           rcChassis16BP-REV-E(4),
           rcChassisRC001-1M-NMS-REV-A(5),
           rcChassisRC001-1M-NMS-REV-B(6),
           rcChassisRC001-2M-NMS-REV-A(7)
        }
        MAX-ACCESS read-only
        STATUS current
        DESCRIPTION
          "
             机箱类型.(1:16槽C版机箱背板,2:16槽D版机箱背板
             ,3:4槽A版机箱背板,4:16槽俄E版机箱背板,5:单槽可网管A版机箱
             ,6:单槽可网管B版机箱,7:双槽可网管A版机箱)
          "
        ::= {rcftChassisEntry 5}

    rcftChassisDescr OBJECT-TYPE
        SYNTAX DisplayString
        MAX-ACCESS read-write
        STATUS current
        DESCRIPTION
          "
             机箱描述
          "
        ::= {rcftChassisEntry 6}


    rcftPowerTable OBJECT-TYPE
        SYNTAX SEQUENCE OF RcftPowerEntry
        MAX-ACCESS not-accessible
        STATUS current
        DESCRIPTION
        "
          电源表,该表包括电源的输入是否是交流以及输出的5V.12V是否存在故障
          The table holding information related to the power status.
        "
        ::= {rcftPower 1}

    rcftPowerEntry OBJECT-TYPE
        SYNTAX RcftPowerEntry
        MAX-ACCESS not-accessible
        STATUS current
        DESCRIPTION
        "
          The power information table.
        "
        INDEX { rcftChassisIndex, rcftPowerIndex }
        ::= {rcftPowerTable 1}

    RcftPowerEntry ::= SEQUENCE {
        rcftPowerIndex
            INTEGER,
        rcftPowerExist
            INTEGER,
        rcft5vStatus
            INTEGER,
        rcft12vStatus
            INTEGER,
        rcft5vAC
            INTEGER,
        rcft12vAC
            INTEGER
    }

    rcftPowerIndex OBJECT-TYPE
        SYNTAX INTEGER
        MAX-ACCESS read-only
        STATUS current
        DESCRIPTION
        "
          电源索引(1-2)
          Power index ranging between 1 and 2.
        "
        ::= {rcftPowerEntry 1}

    rcftPowerExist OBJECT-TYPE
        SYNTAX INTEGER
        {
            exist(1),
            notExist(2)
        }
        MAX-ACCESS read-only
        STATUS current
        DESCRIPTION
        "
          电源是否存在(1:存在,2:不存在).  如果电源不存在,针对该电源的其他状态:
          rcftPowerAC.rcft5vStatus和rcft12vStatus的值是0,此时取这些值没有意义.
          The value of this object indicates whether the power is exist.When the power
          is exist the value of this object is exist(1),otherwise notExist(2).
          Note:When the power is not exist the value of the status such as rcft5vStatus, rcft12vStatus
          and rcftACPower is 0 which means no meaning.
        "
        ::= {rcftPowerEntry 2}

    rcft5vStatus OBJECT-TYPE
        SYNTAX INTEGER
        {
            normal(1),
            abnormal(2)
        }
        MAX-ACCESS read-only
        STATUS current
        DESCRIPTION
        "
          电源的5v输出是否正常(1:正常,2:不正常).
          注:机箱有两个电源,每个电源有交流和直流两种供电方式,其输出电压有5v和12v两种.
        "
        ::= {rcftPowerEntry 3}

    rcft12vStatus OBJECT-TYPE
        SYNTAX INTEGER
        {
            normal(1),
            abnormal(2)
        }
        MAX-ACCESS read-only
        STATUS current
        DESCRIPTION
        "
          输出电压是12伏的电源状态(1:正常,2:不正常).
          The value of this object indicates the 12v-output of the power is normal or not.
          1: normal
          2: abnormal
        "
        ::= {rcftPowerEntry 4}

    rcft5vAC OBJECT-TYPE
        SYNTAX INTEGER
        {
            ac(1),
            dc(2)
        }
        MAX-ACCESS read-only
        STATUS current
        DESCRIPTION
        " 5伏电源供电状态(1:220交流,2:-48V直流).
          Chassis power-supply mode:
           1: AC
           2: DC
        "
        ::= {rcftPowerEntry 5}

    rcft12vAC OBJECT-TYPE
        SYNTAX INTEGER
        {
            ac(1),
            dc(2)
        }
        MAX-ACCESS read-only
        STATUS current
        DESCRIPTION
          " 12伏电源供电状态(1:220交流,2:-48V直流). "
        ::= {rcftPowerEntry 6}

    rcftFanTable OBJECT-TYPE
        SYNTAX SEQUENCE OF RcftFanEntry
        MAX-ACCESS not-accessible
        STATUS current
        DESCRIPTION
        "
          The table holding information related to the fan status.
        "
        ::= {rcftFan 1}

    rcftFanEntry OBJECT-TYPE
        SYNTAX RcftFanEntry
        MAX-ACCESS not-accessible
        STATUS current
        DESCRIPTION
        "
           The fan information entry.
        "
        INDEX { rcftChassisIndex, rcftFanIndex }
        ::= {rcftFanTable 1}

    RcftFanEntry ::= SEQUENCE {
        rcftFanIndex
            INTEGER,
        rcftFanLoc
            INTEGER,
        rcftFanStatus
            INTEGER
    }

    rcftFanIndex OBJECT-TYPE
        SYNTAX INTEGER
        MAX-ACCESS read-only
        STATUS current
        DESCRIPTION
        "
          风扇索引(1-3)
          Fan index ranging between 1 and 3.
        "
        ::= {rcftFanEntry 1}

    rcftFanLoc OBJECT-TYPE
        SYNTAX INTEGER
        {
            fixed(1),
            ps1(2),
            ps2(3)
        }
        MAX-ACCESS read-only
        STATUS current
        DESCRIPTION
          " 风扇位置(1:机箱固定风扇,2:PS1,3:PS2). "
        ::= {rcftFanEntry 2}

    rcftFanStatus OBJECT-TYPE
        SYNTAX INTEGER
        {
            normal(1),
            abnormal(2)
        }
        MAX-ACCESS read-only
        STATUS current
        DESCRIPTION
        "
          风扇状态(1:正常,2:不正常).
          This object indicates whether the work status of the fan is normal or not.
          1: normal
          2: abnormal
        "
        ::= {rcftFanEntry 3}


    rcftSlotStatTable OBJECT-TYPE
        SYNTAX SEQUENCE OF RcftSlotStatEntry
        MAX-ACCESS not-accessible
        STATUS current
        DESCRIPTION
        "
          The table holding information related to the card status.
          注:表中的对象是所有板卡状态对象的全集,针对某一类型的板卡,
          只有与其相关的状态对象有意义,而其它的对象值没有意义,被清0.
        "
        ::= {rcftSlotStat 1}

    rcftSlotStatEntry OBJECT-TYPE
        SYNTAX RcftSlotStatEntry
        MAX-ACCESS not-accessible
        STATUS current
        DESCRIPTION
        "
          The card information entry.
        "
        INDEX { rcftChassisIndex, rcftSlotIndex }
        ::= {rcftSlotStatTable 1}

    RcftSlotStatEntry ::= SEQUENCE {
        rcftSlotIndex
            INTEGER,
        rcftSlotExist
            INTEGER,
        rcftSlotType
            INTEGER,
        rcftSlotFaultPass
            INTEGER,
        rcftSlotVLAN
            INTEGER,
        rcftSlotConfigStatus
            INTEGER,
        rcftSlotELink
            INTEGER,
        rcftSlotEAutoNegotiation
            INTEGER,
        rcftSlotEDuplex
            INTEGER,
        rcftSlotECollCount
            INTEGER,
        rcftSlotESpeed
            INTEGER,
        rcftSlotETxStatus
            INTEGER,
        rcftSlotERxStatus
            INTEGER,
        rcftSlotOLink
            INTEGER,
        rcftSlotODuplex
            INTEGER,
        rcftSlotOSpeed
            INTEGER,
        rcftSlotOTxStatus
            INTEGER,
        rcftSlotORxStatus
            INTEGER,
        rcftSlotDescr
            OCTET STRING,
        rcftSlotORLnk
            INTEGER,
        rcftSlotOTLnk
            INTEGER,
        rcftSlotORmd
            INTEGER,
        rcftSlotOFxAct
            INTEGER,
        rcftSlotETxAct
            INTEGER,
        rcftSlotRemManage
            INTEGER,
        rcftSlotLBKTest
            INTEGER,
        rcftSlotVOLimit
            INTEGER,
        rcftSlotVBLimit
            INTEGER,
        rcftSlotLBKTestOk
    	    INTEGER,
    	rcftSlotEPort
    	    INTEGER,
        rcftSlotOSendPower
            INTEGER,
        rcftSlotOReceSen
            INTEGER,
        rcftSlotOLaser
            INTEGER,
        rcftSlotOSD
            INTEGER,
        rcftSlotOPort
            INTEGER,
        rcftSlotOrder
            INTEGER,
        rcftRSlotExist
            INTEGER,
        rcftRSlotEAutoNegotiation
            INTEGER,
        rcftRSlotEDuplex
            INTEGER,
        rcftRSlotELink
            INTEGER,
        rcftRSlotFaultPass
            INTEGER,
        rcftRSlotEPort
    	    INTEGER,
        rcftRSlotRemManage
            INTEGER,
        rcftRSlotVOLimit
            INTEGER,
        rcftRSlotVBLimit
            INTEGER,
        rcftRSlotOSendPower
            INTEGER,
        rcftRSlotOReceSen
            INTEGER,
        rcftRSlotOLaser
            INTEGER,
        rcftRSlotOSD
            INTEGER,
        rcftRSlotOLink
            INTEGER,
        rcftRSlotOrder
            INTEGER,
        rcftSlotRowStatus
            INTEGER,
        rcftRSlotType
            INTEGER,
        rcftRSlotChassisTmpt
            INTEGER,
        rcftSlotExSwitchMode
            INTEGER,
        rcftSlotRevFluxCount
            Counter32,
        rcftSlotSedFluxCount
            Counter32,
        rcftSlotRevFluxTimer
            Counter32,
        rcftSlotSedFluxTimer
           Counter32,
        rcftRSlotESpeed
            INTEGER,
        rcftRSlotOSpeed
            INTEGER,
        rcftRSlotORLnk
            INTEGER,
        rcftRSlotOTLnk
            INTEGER,
        rcftSlotE1LOS
            INTEGER,
        rcftSlotOLOS
            INTEGER,
        rcftSlotOSync
            INTEGER,
        rcftSlotOTransErrorCode
            INTEGER,
        rcftRSlotE1LOS
            INTEGER,
        rcftRSlotOLOS
            INTEGER,
        rcftRSlotOSync
            INTEGER,
        rcftRSlotOTransErrorCode
            INTEGER,
        rcftSlotE1LOF
            INTEGER,
        rcftSlotE1CRC
            INTEGER,
		rcftSlotHardWareDescr
	    	DisplayString,
		rcftSlotSigleChipDescr
	    	DisplayString,
		rcftSlotV35Port
            INTEGER,
		rcftSlotV35RTS
            INTEGER,
		rcftSlotV35DTR
            INTEGER,
		rcftSlotE1LoopStatus
            INTEGER,
		rcftSlotE1LoopSwitchStatus
            INTEGER,
		rcftSlotV35LoopStatus
            INTEGER,
		rcftSlotV35LoopSwitchStatus
            INTEGER,
        rcftSlotEPort1Link
            INTEGER,
        rcftSlotEPort1AutoNegotiation
            INTEGER,
        rcftSlotEPort1Duplex
            INTEGER,
        rcftSlotEPort1Speed
            INTEGER,
    	rcftSlotEPort1Port
    	    INTEGER,
        rcftSlotE2PortBandWidth
            INTEGER,
		rcftSlotV35Speed
            INTEGER,
        rcftSlotV35RateCfg
            INTEGER,
        rcftSlotV35RxClk
            INTEGER,
        rcftSlotV35TxClk
            INTEGER,
        rcftSlotV35LoopTest
            INTEGER,
        rcftSlotRE1LoopTest
            INTEGER,
        rcftSlotRE1LoopStatus
            INTEGER,
        rcftSlotLoopTestEn
            INTEGER,
        rcftSlotCLKMode
            INTEGER,
        rcftSlotCfgCmdEn
            INTEGER,
        rcftSlotE1PCM
            INTEGER,
        rcftSlotE1CRCEn
            INTEGER,
        rcftSlotE1AIS
            INTEGER,
        rcftSlotRALM
            INTEGER,
		rcftSlotE1Transparent
            INTEGER,
		rcftSlotEthTransmitSpeed
            INTEGER,
        rcftSlotE1Port2LOS
            INTEGER,
        rcftRSlotE1Port2LOS
            INTEGER,
		rcftSlotRE1LoopSwitchStatus
            INTEGER,
		rcftSlotFrameLength
            INTEGER,
        rcftSlotRecvRestrictSpeed
            INTEGER,
        rcftSlotSendRestrictSpeed
            INTEGER,
		rcftRSlotFrameLength
            INTEGER,
		rcftRSlotVLAN
            INTEGER,
        rcftSlotLALM
            INTEGER,
		rcftSlotChipOpMode
	    	INTEGER,
        rcftSlotAutoCutErrLineEn
            INTEGER,
		rcftSlotRamBD
	    	INTEGER,
		rcftSlotV35DSR
	    	INTEGER,
		rcftSlotV35DCD
	    	INTEGER,
        rcftRSlotRecvRestrictSpeed
            INTEGER,
        rcftRSlotSendRestrictSpeed
            INTEGER,
		rcftRSlotV35Speed
            INTEGER,
        rcftRSlotCLKMode
            INTEGER,
        rcftSlotWorkStatus
            INTEGER,
        rcftTxWorkStatus
            INTEGER,
        rcftFxWorkStatus
            INTEGER,
        rcftE1WorkStatus
            INTEGER,
        rcftV35WorkStatus
            INTEGER,
        rcftAllLoopSwitch
            INTEGER,
        rcftSlotE1PortAlarm
            INTEGER,
        rcftRSlotE1PortAlarm
            INTEGER,
		rcftRSlotHardWareDescr
	    	DisplayString,
		rcftRSlotSigleChipDescr
	    	DisplayString,
		rcftSlotConfCardType
            INTEGER,
        rcftSlotLineStatus
            INTEGER,
        rcftV35E1PortExtendStatus
            INTEGER,
        rcftSlotDoubleLoopSwitch
            INTEGER,
        rcftRSlotDoubleLoopSwitch
            INTEGER,
		rcftRSlotOport
            INTEGER,
		cwdmClientWorkSpeed
			INTEGER,
		cwdmCWDMWorkStatus
		    INTEGER,
		cwdmCWDMModuleMaxSpeed
			INTEGER,
		cwdmCWDMModuleTransLen
		    INTEGER,
		cwdmCWDMModuleWaveLen
		   INTEGER,
		cwdmCWDMModuleManufacturer
		   OCTET STRING,
		cwdmCWDMModuleDescr
		   OCTET STRING,
		cwdmCWDMModuleVersion
		   OCTET STRING,
		cwdmCWDMModuleSerialNumber
		   OCTET STRING,
		cwdmClientWorkStatus
		   INTEGER,
		cwdmClientModuleMaxSpeed
		   INTEGER,
		cwdmClientModuleInterfaceType
		   INTEGER,
		cwdmClientModuleTransLen
		   INTEGER,
		cwdmClientModuleWaveLen
		   INTEGER,
		cwdmClientModuleManufacturer
		  OCTET STRING,
		cwdmClientModuleDescr
		  OCTET STRING,
		cwdmClientModuleVersion
		  OCTET STRING,
		cwdmClientModuleSerialNumber
		  OCTET STRING,
		cwdmCWDMWorkSpeed
			INTEGER,
		opticalModuleType
			INTEGER,
		rcftSlotInformation
			OCTET STRING,
		remoteOpticalModuleType
			INTEGER,
		rcftRSlotInformation
			OCTET STRING,
		rcftRSlotRevFluxCount
			INTEGER,
		rcftRSlotSedFluxCount
			INTEGER,
		rcftRSlotRevFluxTimer
			INTEGER,
		rcftRSlotSedFluxTimer
			INTEGER,
		rcftSlotRevErrFluxCnt
			INTEGER,
		rcftSlotSedErrFluxCnt
			INTEGER,
		cwdmOMUmoduleType
			INTEGER,
		rcftSlotE1TimeSlot
			Unsigned32,
		rcftSlotWANRevFluxPacket
			INTEGER,
		rcftSlotWANRevFluxCount
			INTEGER,
		rcftSlotWANSedFluxPacket
			INTEGER,
        rcftSlotWANSedFluxCount
        	INTEGER,
        rcftSlotWANRevErrFluxPacket
        	INTEGER,
        rcftSlotRevFluxPacket
        	INTEGER,
        rcftSlotSedFluxPacket
        	INTEGER,
        rcftRSlotE1TimeSlot
        	Unsigned32,
        rcftRSlotWANRevFluxPacket
        	INTEGER,
        rcftRSlotWANRevFluxCount
        	INTEGER,
        rcftRSlotWANSedFluxPacket
        	INTEGER,
        rcftRSlotWANSedFluxCount
        	INTEGER,
        rcftRSlotWANRevErrFluxPacket
        	INTEGER,
        rcftRSlotRevFluxPacket
        	INTEGER,
        rcftRSlotSedFluxPacket
        	INTEGER,
        rcftRSlotRevErrFluxCnt
		  	INTEGER,
		rcftExtentWorkStatus
			INTEGER,
		rcftSlotE1ESCnt
			INTEGER,
		rcftSlotE1SESCnt
			INTEGER,
		rcftRSlotE1ESCnt
			INTEGER,
		rcftRSlotE1SESCnt
			INTEGER,
		rcftRSlotCWDMModuleMaxSpeed
			INTEGER,
		rcftRSlotCWDMModuleTransLen
		    INTEGER,
		rcftRSlotCWDMModuleWaveLen
		   INTEGER,
		rcftRSlotCWDMModuleManufacturer
		   OCTET STRING,
		rcftRSlotCWDMModuleDescr
		   OCTET STRING,
		rcftRSlotCWDMModuleVersion
		   OCTET STRING,
		rcftRSlotCWDMModuleSerialNumber
		   OCTET STRING,
		rcftSlotLANOPortModuleType
			INTEGER,
		rcftSlotWANOPortModuleType
			INTEGER,
		rcftSlotCDRSpeed
			INTEGER,
		rcftRSlotManufacturer
		   OCTET STRING,
		rcftRSlotSoftwareVersion
		   OCTET STRING,
		rcftRSlotVoltageValue
			Unsigned32,
		rcftRSlotCommunityRW
			INTEGER,
		rcftRSlotCommunity
			OCTET STRING,
		rcftRSlotDeviceIP
			OCTET STRING,
		rcftSlotLinePortSpeed
			INTEGER,
		rcftSlotLinePortMaxSpeed
			INTEGER,
		rcftSlotLinePortMinSpeed
			INTEGER,
		rcftSlotLinePortSNR
			INTEGER,
		rcftSlotLinePortLinkUpTime
			Unsigned32,
		rcftRSlotLinePortSNR
			INTEGER,
		rcftRSlotLinePortLinkUpTime
			Unsigned32,
		rcftRSlotLinePortSpeed
			INTEGER,
		rcftSlotOrderParameter
			INTEGER,
	    rcftRSlotOrderParameter
			INTEGER,
        rcftSlotRevErrFluxPacket
			INTEGER,
		rcftRSlotRevErrFluxPacket
			INTEGER,
		rcftRSlotLinePortType
			INTEGER,
		rcftRSlotManageChannelSel
			INTEGER,
		rcftRSlotManageChannelTSNum
			INTEGER,
		rcftRSlotV35TimeSlots
			Unsigned32,
		rcftSlotLinePortSNRConf
			INTEGER,
		rcftRSlotLANOPortModuleType
			INTEGER,
		rcftRSlotConfigFlag
			INTEGER,
		rcftSlotOpticalDeviceStatus
			INTEGER,
		rcftSlotPrimaryAdjustFactor
			INTEGER,
		rcftSlotPrimaryOpticalRate
			OCTET STRING,
		rcftSlotPrimaryTrapThreshold
			OCTET STRING,
		rcftSlotSecondaryAdjustFactor
			INTEGER,
		rcftSlotSecondaryOpticalRate
			OCTET STRING,
		rcftSlotSecondaryTrapThreshold
			OCTET STRING,
		rcftSlotWANSendErrFluxPacket
			INTEGER,
		rcftRSlotWANSendErrFluxPacket
			INTEGER,
		rcftSlotOpticalDeviceType
			INTEGER,
		rcftRSlotCardOrderInfor
			OCTET STRING,
        rcftRSlotTimeSlots
            OCTET STRING,
		rcftRSlotServiceConnectMode
			INTEGER,
		rcftSlotSendErrFluxPacket
			INTEGER,
		rcftRSlotSendErrFluxPacket
			INTEGER,
		cwdmSecondaryCWDMModuleMaxSpeed
			INTEGER,
		cwdmSecondaryCWDMModuleTransLen
		    INTEGER,
		cwdmSecondaryCWDMModuleWaveLen
		   INTEGER,
		cwdmSecondaryCWDMModuleManufacturer
		   OCTET STRING,
		cwdmSecondaryCWDMModuleDescr
		   OCTET STRING,
		cwdmSecondaryCWDMModuleVersion
		   OCTET STRING,
		cwdmSecondaryCWDMModuleSerialNumber
		   OCTET STRING,
		rcftSlotVLANTagDirection
		   INTEGER,
		rcftRSlotVLANTagDirection
		   INTEGER,
		rcftSlotVLANTagModule
		   INTEGER,
		rcftRSlotVLANTagModule
		   INTEGER,
		rcftSlotVLANID
		   INTEGER,
		rcftRSlotVLANID
		   INTEGER,
		rcftSlotISPTPID
		   INTEGER,
		rcftRSlotISPTPID
		   INTEGER,
		rcftSlotE1SubCardType
		   INTEGER,
		rcftSlotMultiE1LoopOrder
			OCTET STRING,
		rcftSlotSubModuleExist
			INTEGER,
		rcftSlotOrderTimeParameter
			INTEGER,
		rcftSlotRLPStatus
			INTEGER,
		rcftSlotSFPDiagnosticsInfo
			INTEGER,
		rcftRSlotSFPDiagnosticsInfo
			INTEGER,
		rcftSlotTemp
			INTEGER,
		rcftSlotLALStatus
			INTEGER,
		rcftSlotRALStatus
			INTEGER,
		rcftSlotCardInformation
			OCTET STRING,
		rcftSlotVoltage
			INTEGER,
		rcftSlotVoltageHighLimit
			INTEGER,
		rcftSlotVoltageLowLimit
			INTEGER,
		rcftSlotTempHighLimit
			INTEGER,
		rcftSlotTempLowLimit
			INTEGER,
		rcftSlotHumidity
			INTEGER,
		rcftSlotHumidityHighLimit
			INTEGER,
		rcftSlotHumidityLowLimit
			INTEGER,
		rcftSlotMultiE1AlarmRejectOrder
			OCTET STRING,
		rcftT1PortPulseWaveForm
		    INTEGER,
		rcftT1PortCodeType
			INTEGER,
		rcftSlotSDRAM
			INTEGER,
		rcftSlotSabitMode
			INTEGER,
		rcftSlotApsWaitToRestore
			INTEGER,
		rcftSlotCLKChannel
			INTEGER,
		rcftSlotRmcChannelType
			INTEGER,
		rcftSlotApsE3SwitchDelay
			INTEGER,
		rcftSlotApsE6SwitchDelay
			INTEGER,
		rcftE1DS1PortType
			INTEGER,
		rcftSlotManageID
			INTEGER,
		rcftSlotE1PortNumber
			INTEGER,
		rcftSlotQoS
			INTEGER,
	    rcftSlotTPIDRemark
	    	INTEGER,
	  	rcftRSlotTPIDRemark
	    	INTEGER,
		rcftSlotDeviceMibUse
			INTEGER,
		rcftSlotApsSwitchDelay
			INTEGER
	   }

    rcftSlotIndex OBJECT-TYPE
        SYNTAX INTEGER
        MAX-ACCESS read-only
        STATUS current
        DESCRIPTION
          "
          	槽位索引(1-16)
          	Slot index ranging between 1 and 16.
          "
        ::= {rcftSlotStatEntry 1}

    rcftSlotExist OBJECT-TYPE
        SYNTAX INTEGER
        {
            exist(1),
            notExist(2)
        }
        MAX-ACCESS read-only
        STATUS current
        DESCRIPTION
          "
          槽位板卡存在状态(1:存在,2:不存在). 当以rcftSlotIndex为索引的槽位不存在板卡时该槽位的
          其它状态没有意义,其值被清零.
          The value of this object indicates whether there is a card inserted in the slot whose index
          is rcftSlotIndex.When the slot has no card inserted in, the objects in the rcftSlotStatTable
          except for rcftSlotIndex and rcftSlotExist are meaningless and their value is 0.
          "
        ::= {rcftSlotStatEntry 2}

    rcftSlotType OBJECT-TYPE
        SYNTAX INTEGER
        {
            rcftTypeRC202-E-M(8),
            rcftTypeRC202-E-S1(9),
            rcftTypeRC202-E-S2(10),
            rcftTypeRC202-E-S3(11),
            rcftTypeRC202-FE-M(12),
            rcftTypeRC202-FE-S1(13),
            rcftTypeRC202-FE-S2(14),
            rcftTypeRC202-FE-S3(15),
            rcftTypeRC102-FE-M(16),
            rcftTypeRC102-FE-S1(17),
            rcftTypeRC102-FE-S2(18),
            rcftTypeRC102-FE-S3(19),
            rcftTypeRC202-GE-M(20),
            rcftTypeRC202-GE-S1(21),
            rcftTypeRC202-GE-S2(22),
            rcftTypeRC202-GE-S3(23),
            rcftTypeRC303-4-FE-M(24),
            rcftTypeRC303-4-FE-S1(25),
            rcftTypeRC303-4-FE-S2(26),
            rcftTypeRC303-4-FE-S3(27),

            rcftTypeRC302-FE-M(28),
            rcftTypeRC302-FE-S1(29),
            rcftTypeRC302-FE-S2(30),
            rcftTypeRC302-FE-S3(31),

            rcftTypeRC402-Gb-M(32),
            rcftTypeRC402-Gb-S1(33),
            rcftTypeRC402-Gb-S2(34),
            rcftTypeRC402-Gb-S3(35),
            rcftTypeRC402-C3-M(36),
            rcftTypeRC402-C3-S1(37),
            rcftTypeRC402-C3-S2(38),
            rcftTypeRC402-C3-S3(39),
            rcftTypeRC303-4-E-M(40),
            rcftTypeRC303-4-E-S1(41),
            rcftTypeRC303-4-E-S2(42),
            rcftTypeRC303-4-E-S3(43),
            rcftTypeRC602-FE-M-REV-A(44),
            rcftTypeRC602-FE-S1-REV-A(45),
            rcftTypeRC602-FE-S2-REV-A(46),
            rcftTypeRC602-FE-S3-REV-A(47),
            rcftTypeRC303-4-GE-M(48),
            rcftTypeRC303-4-GE-S1(49),
            rcftTypeRC303-4-GE-S2(50),
            rcftTypeRC303-4-GE-S3(51),
            rcftTypeRC305-6-FE-M(52),
            rcftTypeRC305-6-FE-S1(53),
            rcftTypeRC305-6-FE-S2(54),
            rcftTypeRC305-6-FE-S3(55),
            rcftTypeRC307-8-C3-M(56),
            rcftTypeRC307-8-C3-S1(57),
            rcftTypeRC307-8-C3-S2(58),
            rcftTypeRC307-8-C3-S3(59),
            rcftTypeRC307-8-Gb-M(64),
            rcftTypeRC307-8-Gb-S1(65),
            rcftTypeRC307-8-Gb-S2(66),
            rcftTypeRC307-8-Gb-S3(67),
            rcftTypeRC502-FE-M-REV-B(72),
            rcftTypeRC502-FE-S1-REV-B(73),
            rcftTypeRC502-FE-S2-REV-B(74),
            rcftTypeRC502-FE-S3-REV-B(75),
            rcftTypeRC102-FE-M-REV-E(76),
            rcftTypeRC102-FE-S1-REV-E(77),
            rcftTypeRC102-FE-S2-REV-E(78),
            rcftTypeRC102-FE-S3-REV-E(79),
            rcftTypeRC202-FE-M-REV-F(80),
            rcftTypeRC202-FE-S1-REV-F(81),
            rcftTypeRC202-FE-S2-REV-F(82),
            rcftTypeRC202-FE-S3-REV-F(83),
            rcftTypeRC102-FE-M-REV-F(84),
            rcftTypeRC102-FE-S1-REV-F(85),
            rcftTypeRC102-FE-S2-REV-F(86),
            rcftTypeRC102-FE-S3-REV-F(87),
            rcftTypeRC202-FE-M-REV-G(88),
            rcftTypeRC202-FE-S1-REV-G(89),
            rcftTypeRC202-FE-S2-REV-G(90),
            rcftTypeRC202-FE-S3-REV-G(91),
            rcftTypeRC602-FE-M-REV-C(92),
            rcftTypeRC602-FE-S1-REV-C(93),
            rcftTypeRC602-FE-S2-REV-C(94),
            rcftTypeRC602-FE-S3-REV-C(95),
            rcftTypeRC305-6-FE-M-REV-B(100),
            rcftTypeRC305-6-FE-S1-REV-B(101),
            rcftTypeRC305-6-FE-S2-REV-B(102),
            rcftTypeRC305-6-FE-S3-REV-B(103),
            rcftTypeRC502-FE-M-REV-C(104),
            rcftTypeRC502-FE-S1-REV-C(105),
            rcftTypeRC502-FE-S2-REV-C(106),
            rcftTypeRC502-FE-S3-REV-C(107),
            rcftTypeRC404-Gb-M(112),
            rcftTypeRC404-Gb-S1(113),
            rcftTypeRC404-Gb-S2(114),
            rcftTypeRC404-Gb-S3(115),
            rcftTypeRC404-C3-M(116),
            rcftTypeRC404-C3-S1(117),
            rcftTypeRC404-C3-S2(118),
            rcftTypeRC404-C3-S3(119),
            rcftTypeRC302-E-M(124),
            rcftTypeRC302-E-S1(125),
            rcftTypeRC302-E-S2(126),
            rcftTypeRC302-E-S3(127),
            rcftTypeRC302-GE-M(132),
            rcftTypeRC302-GE-S1(133),
            rcftTypeRC302-GE-S2(134),
            rcftTypeRC302-GE-S3(135),
            rcftTypeRC302-FE-M-REV-B(136),
            rcftTypeRC302-FE-S1-REV-B(137),
            rcftTypeRC302-FE-S2-REV-B(138),
            rcftTypeRC302-FE-S3-REV-B(139),
            rcftTypeRC301-FE-M-REV-A(140),
            rcftTypeRC301-FE-S1-REV-A(141),
            rcftTypeRC301-FE-S2-REV-A(142),
            rcftTypeRC301-FE-S3-REV-A(143),
            rcftTypeRC303-4-FE-M-REV-B(152),
            rcftTypeRC303-4-FE-S1-REV-B(153),
            rcftTypeRC303-4-FE-S2-REV-B(154),
            rcftTypeRC303-4-FE-S3-REV-B(155),
            rcftTypeRC604-FE-M-REV-C(156),
            rcftTypeRC604-FE-S1-REV-C(157),
            rcftTypeRC604-FE-S2-REV-C(158),
            rcftTypeRC604-FE-S3-REV-C(159),
            rcftTypeRC504-FE-M-REV-C(164),
            rcftTypeRC504-FE-S1-REV-C(165),
            rcftTypeRC504-FE-S2-REV-C(166),
            rcftTypeRC504-FE-S3-REV-C(167),
            rcftTypeRC504-E-M-REV-C(172),
            rcftTypeRC504-E-S1-REV-C(173),
            rcftTypeRC504-E-S2-REV-C(174),
            rcftTypeRC504-E-S3-REV-C(175),
            rcftTypeRC302-C3-M-REV-A(180),
            rcftTypeRC302-C3-S1-REV-A(181),
            rcftTypeRC302-C3-S2-REV-A(182),
            rcftTypeRC302-C3-S3-REV-A(183),
            rcftTypeRC302-Gb-M-REV-A(184),
            rcftTypeRC302-Gb-S1-REV-A(185),
            rcftTypeRC302-Gb-S2-REV-A(186),
            rcftTypeRC302-Gb-S3-REV-A(187),
            rcftTypeRC302-C12-M-REV-A(188),
            rcftTypeRC302-C12-S1-REV-A(189),
            rcftTypeRC302-C12-S2-REV-A(190),
            rcftTypeRC302-C12-S3-REV-A(191),
            rcftTypeRC402-C12-M-REV-A(192),
            rcftTypeRC402-C12-S1-REV-A(193),
            rcftTypeRC402-C12-S2-REV-A(194),
            rcftTypeRC402-C12-S3-REV-A(195),
            rcftTypeRC404-C12-M-REV-A(200),
            rcftTypeRC404-C12-S1-REV-A(201),
            rcftTypeRC404-C12-S2-REV-A(202),
            rcftTypeRC404-C12-S3-REV-A(203),
            rcftTypeRC307-8-C12-M(204),
            rcftTypeRC307-8-C12-S1(205),
            rcftTypeRC307-8-C12-S2(206),
            rcftTypeRC307-8-C12-S3(207),
            rcftTypeRC606-FE-M-REV-C(208),
            rcftTypeRC606-FE-S1-REV-C(209),
            rcftTypeRC606-FE-S2-REV-C(210),
            rcftTypeRC606-FE-S3-REV-C(211),
            rcftTypeRC506-FE-M-REV-C(216),
            rcftTypeRC506-FE-S1-REV-C(217),
            rcftTypeRC506-FE-S2-REV-C(218),
            rcftTypeRC506-FE-S3-REV-C(219),
            rcftTypeRC802-30-G703E1-M(224),
            rcftTypeRC802-30-G703E1-S1(225),
            rcftTypeRC802-30-G703E1-S2(226),
            rcftTypeRC802-30-G703E1-S3(227),
            rcftTypeRC502-E-M-REV-C(228),
            rcftTypeRC502-E-S1-REV-C(229),
            rcftTypeRC502-E-S2-REV-C(230),
            rcftTypeRC502-E-S3-REV-C(231),
            rcftTypeRC506-E-M-REV-C(236),
            rcftTypeRC506-E-S1-REV-C(237),
            rcftTypeRC506-E-S2-REV-C(238),
            rcftTypeRC506-E-S3-REV-C(239),
            rcftTypeRC902-EE1-REV-B(252),
	    rcftTypeRC904-V35E1-REV-A(256),
            rcftTypeRC102-2FE-M-REV-A(268),
            rcftTypeRC102-2FE-S1-REV-A(269),
            rcftTypeRC102-2FE-S2-REV-A(270),
            rcftTypeRC102-2FE-S3-REV-A(271),
            rcftTypeRC305-6-2FE-M-REV-A(272),
	    rcftTypeRC305-6-2FE-S1-REV-A(273),
	    rcftTypeRC305-6-2FE-S2-REV-A(274),
	    rcftTypeRC305-6-2FE-S3-REV-A(275),
            rcftTypeRC802-30-G703-M-REV-B(276),
	    rcftTypeRC802-30-G703-S1-REV-B(277),
	    rcftTypeRC802-30-G703-S2-REV-B(278),
	    rcftTypeRC802-30-G703-S3-REV-B(279),
            rcftTypeRC904-V35FE1-REV-B(280),
            rcftTypeRC906-EE1-REV-A(284),
            rcftTypeRC804-30-G703-M-REV-B(288),
	    rcftTypeRC804-30-G703-S1-REV-B(289),
	    rcftTypeRC804-30-G703-S2-REV-B(290),
	    rcftTypeRC804-30-G703-S3-REV-B(291),
            rcftTypeRC802-60B-G703-M-REV-A(292),
	    rcftTypeRC802-60B-G703-S1-REV-A(293),
	    rcftTypeRC802-60B-G703-S2-REV-A(294),
	    rcftTypeRC802-60B-G703-S3-REV-A(295),
            rcftTypeRC804-60B-G703-M-REV-A(296),
	    rcftTypeRC804-60B-G703-S1-REV-A(297),
	    rcftTypeRC804-60B-G703-S2-REV-A(298),
	    rcftTypeRC804-60B-G703-S3-REV-A(299),
            rcftTypeRC608-FE-M-REV-C(304),
            rcftTypeRC608-FE-S1-REV-C(305),
            rcftTypeRC608-FE-S2-REV-C(306),
            rcftTypeRC608-FE-S3-REV-C(307),
            rcftTypeRC512-FE-M-REV-A(312),
            rcftTypeRC512-FE-S1-REV-A(313),
            rcftTypeRC512-FE-S2-REV-A(314),
            rcftTypeRC512-FE-S3-REV-A(315),
            rcftTypeRC609-FE-M-REV-C(320),
            rcftTypeRC609-FE-S1-REV-C(321),
            rcftTypeRC609-FE-S2-REV-C(322),
            rcftTypeRC609-FE-S3-REV-C(323),
            rcftTypeRC514-FE-M-REV-A(328),
            rcftTypeRC514-FE-S1-REV-A(329),
            rcftTypeRC514-FE-S2-REV-A(330),
            rcftTypeRC514-FE-S3-REV-A(331),
            rcftTypeRC102-FE-M-REV-G(336),
            rcftTypeRC102-FE-S1-REV-G(337),
            rcftTypeRC102-FE-S2-REV-G(338),
            rcftTypeRC102-FE-S3-REV-G(339),
            rcftTypeRC305-6-FE-M-REV-C(340),
            rcftTypeRC305-6-FE-S1-REV-C(341),
            rcftTypeRC305-6-FE-S2-REV-C(342),
            rcftTypeRC305-6-FE-S3-REV-C(343),
            rcftTypeRC112-FE-M-REV-A(344),
            rcftTypeRC112-FE-S1-REV-A(345),
            rcftTypeRC112-FE-S2-REV-A(346),
            rcftTypeRC112-FE-S3-REV-A(347),
            rcftTypeRC315-6-FE-M-REV-A(348),
            rcftTypeRC315-6-FE-S1-REV-A(349),
            rcftTypeRC315-6-FE-S2-REV-A(350),
            rcftTypeRC315-6-FE-S3-REV-A(351),
            rcftTypeRC202-C3-FE-M-REV-A(368),
            rcftTypeRC202-C3-FE-S1-REV-A(369),
            rcftTypeRC202-C3-FE-S2-REV-A(370),
            rcftTypeRC202-C3-FE-S3-REV-A(371),
            rcftTypeRC303-4-C3-FE-M-REV-A(372),
            rcftTypeRC303-4-C3-FE-S1-REV-A(373),
            rcftTypeRC303-4-C3-FE-S2-REV-A(374),
            rcftTypeRC303-4-C3-FE-S3-REV-A(375),
            rcftTypeRC802-30B-FV35-M-REV-A(376),
            rcftTypeRC802-30B-FV35-S1-REV-A(377),
            rcftTypeRC802-30B-FV35-S2-REV-A(378),
            rcftTypeRC802-30B-FV35-S3-REV-A(379),
            rcftTypeRC804-30B-FV35-M-REV-A(380),
            rcftTypeRC804-30B-FV35-S1-REV-A(381),
            rcftTypeRC804-30B-FV35-S2-REV-A(382),
            rcftTypeRC804-30B-FV35-S3-REV-A(383),
            rcftTypeRC512-FE-M-REV-A-SLAVE (400),
            rcftTypeRC512-FE-S1-REV-A-SLAVE(401),
            rcftTypeRC512-FE-S2-REV-A-SLAVE(402),
            rcftTypeRC512-FE-S3-REV-A-SLAVE(403),
            rcftTypeRC906-FE1-REV-B(404),
            rcftTypeRC902-FE4E1-REV-A(408),
            rcftTypeRC908-EV35-REV-B(412),
            rcftTypeRC112-2FE-M-REV-A(416),
            rcftTypeRC112-2FE-S1-REV-A(417),
            rcftTypeRC112-2FE-S2-REV-A(418),
            rcftTypeRC112-2FE-S3-REV-A(419),
            rcftTypeRC315-6-2FE-M-REV-A(424),
            rcftTypeRC315-6-2FE-S1-REV-A(425),
            rcftTypeRC315-6-2FE-S2-REV-A(426),
            rcftTypeRC315-6-2FE-S3-REV-A(427),
            rcftTypeRCMS2201-30-REV-A(428),
            rcftTypeRCMS2201-30-S1-REV-A(429),
            rcftTypeRCMS2201-30-S2-REV-A(430),
            rcftTypeRCMS2201-30-S3-REV-A(431),
            rcftTypeRCMS2401-30-M-REV-A(432),
            rcftTypeRCMS2401-30-S1-REV-A(433),
            rcftTypeRCMS2401-30-S2-REV-A(434),
            rcftTypeRCMS2401-30-S3-REV-A(435),
            rcftTypeRCMS2601-30-M-REV-A(436),
            rcftTypeRCMS2601-30-S1-REV-A(437),
            rcftTypeRCMS2601-30-S2-REV-A(438),
            rcftTypeRCMS2601-30-S3-REV-A(439),
            rcftTypeRCMS2101-30-FV35-M-REV-A(440),
            rcftTypeRCMS2101-30-FV35-S1-REV-A(441),
            rcftTypeRCMS2101-30-FV35-S2-REV-A(442),
            rcftTypeRCMS2101-30-FV35-S3-REV-A(443),
            rcftTypeRCMS2501-30-FV35-M-REV-A(444),
            rcftTypeRCMS2501-30-FV35-S1-REV-A(445),
            rcftTypeRCMS2501-30-FV35-S2-REV-A(446),
            rcftTypeRCMS2501-30-FV35-S3-REV-A(447),

            rcftTypeRC202-FE-M-NEW-REV-G(448),  --ssl modify
            rcftTypeRC202-FE-S1-NEW-REV-G(449),
            rcftTypeRC202-FE-S2-NEW-REV-G(450),
            rcftTypeRC202-FE-S3-NEW-REV-G(451),

            rcftTypeRC522-FE-M-REV-A(452),
            rcftTypeRC522-FE-S1-REV-A(453),
            rcftTypeRC522-FE-S2-REV-A(454),
            rcftTypeRC522-FE-S3-REV-A(455),
            rcftTypeRC522-FE-SDM-REV-A(456),
            rcftTypeRC522-FE-SDS1-REV-A(457),
            rcftTypeRC522-FE-SDS2-REV-A(458),
            rcftTypeRC522-FE-SDS3-REV-A(459),
            rcftTypeRC522-FE-SSM-REV-A(460),
            rcftTypeRC522-FE-SSS1-REV-A(461),
            rcftTypeRC522-FE-SSS2-REV-A(462),
            rcftTypeRC522-FE-SSS3-REV-A(463),
            rcftTypeRC802-30B-FV35-M-REV-M(476),
            rcftTypeRC802-30B-FV35-S1-REV-M(477),
            rcftTypeRC802-30B-FV35-S2-REV-M(478),
            rcftTypeRC802-30B-FV35-S3-REV-M(479),
            rcftTypeRC804-30B-FV35-M-REV-M(488),
            rcftTypeRC804-30B-FV35-S1-REV-M(489),
            rcftTypeRC804-30B-FV35-S2-REV-M(490),
            rcftTypeRC804-30B-FV35-S3-REV-M(491),
            rcftTypeRC602-FE-M-REV-E(500),
            rcftTypeRC602-FE-S1-REV-E(501),
            rcftTypeRC602-FE-S2-REV-E(502),
            rcftTypeRC602-FE-S3-REV-E(503),
            rcftTypeRCMS2201-60-REV-A(508),
            rcftTypeRCMS2201-60-S1-REV-A(509),
            rcftTypeRCMS2201-60-S2-REV-A(510),
            rcftTypeRCMS2201-60-S3-REV-A(511),
            rcftTypeRCMS2401-60-M-REV-A(512),
            rcftTypeRCMS2401-60-S1-REV-A(513),
            rcftTypeRCMS2401-60-S2-REV-A(514),
            rcftTypeRCMS2401-60-S3-REV-A(515),
            rcftTypeRCMS2601-60-M-REV-A(516),
            rcftTypeRCMS2601-60-S1-REV-A(517),
            rcftTypeRCMS2601-60-S2-REV-A(518),
            rcftTypeRCMS2601-60-S3-REV-A(519),
            rcftTypeRC303-4-FE-M-REV-G(520),
            rcftTypeRC303-4-FE-S1-REV-G(521),
            rcftTypeRC303-4-FE-S2-REV-G(522),
            rcftTypeRC303-4-FE-S3-REV-G(523),
            rcftTypeRC301-2-FE-M-REV-G(524),
            rcftTypeRC301-2-FE-S1-REV-G(525),
            rcftTypeRC301-2-FE-S2-REV-G(526),
            rcftTypeRC301-2-FE-S3-REV-G(527),
            rcftTypeRC516-FE-M-REV-A(532),
            rcftTypeRC516-FE-S1-REV-A(533),
            rcftTypeRC516-FE-S2-REV-A(534),
            rcftTypeRC516-FE-S3-REV-A(535),
            rcftTypeRC312-FE-M-REV-A(544),
            rcftTypeRC312-FE-S1-REV-A(545),
            rcftTypeRC312-FE-S2-REV-A(546),
            rcftTypeRC312-FE-S3-REV-A(547),
            rcftTypeRC604-FE-M-REV-E(548),
            rcftTypeRC604-FE-S1-REV-E(549),
            rcftTypeRC604-FE-S2-REV-E(550),
            rcftTypeRC604-FE-S3-REV-E(551),
            rcftTypeRC606-FE-M-REV-E(556),
            rcftTypeRC606-FE-S1-REV-E(557),
            rcftTypeRC606-FE-S2-REV-E(558),
            rcftTypeRC606-FE-S3-REV-E(559),
            rcftTypeRC802-30-G703-M-REV-M(564),
	    rcftTypeRC802-30-G703-S1-REV-M(565),
	    rcftTypeRC802-30-G703-S2-REV-M(566),
	    rcftTypeRC802-30-G703-S3-REV-M(567),
            rcftTypeRC804-30-G703-M-REV-M(568),
	    rcftTypeRC804-30-G703-S1-REV-M(569),
	    rcftTypeRC804-30-G703-S2-REV-M(570),
	    rcftTypeRC804-30-G703-S3-REV-M(571),
            rcftTypeRC806-30-G703-M-REV-M(572),
	    rcftTypeRC806-30-G703-S1-REV-M(573),
	    rcftTypeRC806-30-G703-S2-REV-M(574),
	    rcftTypeRC806-30-G703-S3-REV-M(575),

	    rcftTypeOPCOM200-OTU1-2R-REV-A(576),
	    rcftTypeOPCOM200-OTU1-3R-REV-A(580),

	    rcftTypeRC906-FXE1-REV-A(584),
        rcftTypeRC916-FXE1-REV-A(588),
	    rcftTypeOPCOM200-OTU2-2R-REV-A(592),

            rcftTypeRC806-30B-FV35-M-REV-M(596),
            rcftTypeRC806-30B-FV35-S1-REV-M(597),
            rcftTypeRC806-30B-FV35-S2-REV-M(598),
            rcftTypeRC806-30B-FV35-S3-REV-M(599),
             rcftTypeOPCOM200-OTU2-3R-REV-A(600),

            rcftTypeRC802-60B-M-REV-M(620),
            rcftTypeRC802-60B-S1-REV-M(621),
            rcftTypeRC802-60B-S2-REV-M(622),
            rcftTypeRC802-60B-S3-REV-M(623),

            rcftTypeRC804-60B-M-REV-M(624),
            rcftTypeRC804-60B-S1-REV-M(625),
            rcftTypeRC804-60B-S2-REV-M(626),
            rcftTypeRC804-60B-S3-REV-M(627),

            rcftTypeRC806-60B-M-REV-M(628),
            rcftTypeRC806-60B-S1-REV-M(629),
            rcftTypeRC806-60B-S2-REV-M(630),
            rcftTypeRC806-60B-S3-REV-M(631),

            rcftTypeRC906-FXE1-M-REV-M(640),
            rcftTypeRC906-FXE1-S1-REV-M(641),
            rcftTypeRC906-FXE1-S2-REV-M(642),
            rcftTypeRC906-FXE1-S3-REV-M(643),

            rcftTypeRC916-FXE1-M-REV-M(644),
            rcftTypeRC916-FXE1-S1-REV-M(645),
            rcftTypeRC916-FXE1-S2-REV-M(646),
            rcftTypeRC916-FXE1-S3-REV-M(647),

            rcftTypeRC906-EE1-REV-M(648),

            rcftTypeRC902-FX4E1-M-REV-A(652),
            rcftTypeRC902-FX4E1-S1-REV-A(653),
            rcftTypeRC902-FX4E1-S2-REV-A(654),
            rcftTypeRC902-FX4E1-S3-REV-A(655),

            rcftTypeRC912-FX4E1-S1-REV-A(657),
            rcftTypeRC912-FX4E1-S2-REV-A(658),

            rcftTypeRC512-FE-MASTER(672),     --对于B版以前未处理的光头类型统一占用的类型号(0x99+0xf)*4 送给网管，占用的是0x99（假号）
            rcftTypeRC512-FE-SLAVE(604),     --对于B版以前未处理的光头类型统一占用的类型号(0x88+0xf)*4 送给网管，占用的是0x88（假号）
     -- new added start
     		rcftTypeRC802-30B-FV35-REV-N(684),
     		rcftTypeRC804-30B-FV35-REV-N(688),
     		rcftTypeRC806-30B-FV35-REV-N(692),
     -- new added end

            rcftTypeRC202-C3-FE-REV-B(728),

            rcftTypeRC512-FE-noOptical1(752),    --当硬件的拨码无意义时显示成这样
            rcftTypeRC512-FE-SS15-REV-A(753),
            rcftTypeRC512-FE-SS25-REV-A(754),
            rcftTypeRC512-FE-SS35-REV-A(755),

            rcftTypeRC512-FE-SS-noOptical1(756),
            rcftTypeRC512-FE-SS13-SLAVE(757),
            rcftTypeRC512-FE-SS23-SLAVE(758),
            rcftTypeRC512-FE-SS34-SLAVE(759),	--对应于RC512-FE-SLAVE（局端slave）

            rcftTypeRC202-FE-M-REV-H(760),
            rcftTypeRC202-FE-S1-REV-H(761),
            rcftTypeRC202-FE-S2-REV-H(762),
            rcftTypeRC202-FE-S3-REV-H(763),

            --以下为约定3扩展设备类型

            rcftTypeRC906H-FEE1-REV-A-SLAVE(1501),
            rcftTypeRC906H-FXE1-REV-A-SLAVE(1502),
            rcftTypeRC906H-FEE1-REV-A-MASTER(2001),
            rcftTypeRC906H-FXE1-REV-A-MASTER(2002),

            rcftTypeRC602-GEF-REV-C-MASTER(2005),    --对应设备设备类型0xB103
            rcftTypeRC602-GEF-REV-C-SLAVE(2006),     --对应设备设备类型0xB104



            rcftTypeOPCOM200-OMU4E-REV-A(10002),
            rcftTypeOPCOM200-FEU1-REV-A-MASTER(10003),
            rcftTypeOPCOM200-FEU1-REV-A-SLAVE(10004),
            rcftTypeRC952-FXE1-REV-A-SLAVE(10006),
            rcftTypeRC952-FEE1-REV-A-SLAVE(10007),
            rcftTypeRC202-GE-REV-C(10016),
            rcftTypeOPCOM200-FEU2-REV-A-MASTER(10018),
            rcftTypeOPCOM200-FEU2-REV-A-SLAVE(10019),
            rcftTypeRC552-FE-REV-A-SLAVE(10021),
            rcftTypeRC952-FXE1-REV-C-SLAVE(10022),
            rcftTypeRC952-FEE1-REV-B-SLAVE(10023),  --对应硬件b版的移动模式 ，硬件b版的其他模式同a版
           	rcftTypeRC906H-FEE1-SLAVE-PRIVATE(10024),
            rcftTypeRC212-GE-REV-A(10027),
            rcftTypeRC414-REV-A(10028),
            rcftTypeRC602-GE-REV-A-SLAVE(10031),
            rcftTypeRC112-GE-REV-A(10033),
            rcftTypeRC1102-FE-REV-A-SLAVE(10038),
            rcftTypeRC1102-FE-REV-A-MASTER(10039),
            rcftTypeRC152-FE-REV-A(10040),
            rcftTypeRC522-FE-REV-B(10041),
            rcftTypeRC132-FE-REV-A(10042),
            rcftTypeRC552-FE-REV-A-MASTER(10043),
            rcftTypeRC522-FE-REV-D-SLAVE(10044),
            rcftTypeRC1102-E1-REV-B-SLAVE(10046),
            rcftTypeRC1102-E1-REV-B-MASTER(10047),
            rcftTypeRC602-GEF-REV-A-SLAVE(10048),
            rcftTypeOPCOM200-GEU1-REV-A-SLAVE(10050),
            rcftTypeRC522-FE-REV-C-MASTER(10052),
            rcftTypeRC522-FE-REV-C-SLAVE(10053),
            rcftTypeRC602-GE-REV-A-MASTER(10054),
            rcftTypeRC1102-V35-REV-B-MASTER(10055),   --增加v35口的接收时钟自适应配置和速率配置
            rcftTypeRC2002-30FE-REV-A(10056),
            rcftTypeRC602-GEF-REV-A-MASTER(10057),
            rcftTypeOPCOM200-2GEM-REV-A(10058),
            rcftTypeOPCOM200-GEU1-REV-A-MASTER(10059),
            rcftTypeOPCOM200-2GEM-REV-NEW(10061),  --取消了光口环回，增加了光口故障转移
            rcftTypeRC1102-V35-MASTER-REV-A(10062),
            rcftTypeRC952-FXE1-REV-A(10063),
            rcftTypeRC952-FEE1-REV-A(10064),
            rcftTypeRC904-V35FE1-REV-C(10065),
            rcftTypeRC1102-V35-SLAVE-REV-A(10067),
            rcftTypeRC904-V35FE1-BL-REV-C(10069),
            rcftTypeRC852-30-REV-A(10071),
            rcftTypeRC852-30-FV35-REV-A(10072),
            rcftTypeRC902-FE4E1-REV-B(10074),
            rcftTypeRC532-2FE-REV-A-MASTER(10076),
            rcftTypeOPCOM200-2GEM-REV-A2(10077),       --增加了sfp性能统计及sfp告警信息
            rcftTypeRC1102-E1-BL-REV-A-MASTER(10078),
            rcftTypeRC1102-V35-REV-B-SLAVE(10079),  	--增加v35口的接收时钟自适应配置和速率配置
            rcftTypeRC532-FE-REV-A-MASTER(10080),
            rcftTypeRC522-FE-REV-D-MASTER(10082),
            rcftTypeRC532-2FE-REV-A-SLAVE(10084),
            rcftTypeRC1102-E1-BL-REV-A-SLAVE(10085),
            rcftTypeRC112-FE-REV-B(10086),
            rcftTypeRC906H-FEE1-MASTER-PRIVATE(10088),
            rcftTypeRC602-GEF-REV-B-SLAVE(10091),    --光口用sfp
            rcftTypeRC532-FE-REV-A-SLAVE(10092),
            rcftTypeRC802-120L-REV-M(10094),
            rcftTypeRC852-30-BL-REV-A(10101),
            rcftTypeOPCOM200-OLP-T-REV-A(10103),
            rcftTypeRC1102-E1-BL-REV-A2-MASTER(10104),---增加了G.bert
            rcftTypeRC1102-V35-REV-A1-MASTER(10106),	---增加了误码测试和性能统计
            rcftTypeRC904-V35FE1-REV-D(10107),
            rcftTypeRC552-GE-REV-A-SLAVE(10112),
            rcftTypeRC552-GE-REV-A-MASTER(10113),
            rcftTypeRC902-FX4E1-BL-REV-B(10122),
            rcftTypeRC1102-E1-BL-REV-A2-SLAVE(10123),---增加了G.bert
            rcftTypeRC1102-V35-REV-A1-SLAVE(10124),	---增加误码测试和性能统计
            rcftTypeRC552-FE-REV-A-MASTER-NEW(10125),--增加了SFP状态的新协议
            rcftTypeRC802-120L-BL-REV-M(10127),
            rcftTypeOPCOM200-OCP1-REV-A(10128),
            rcftTypeRC552-FE-REV-A-SLAVE-NEW(10130),--增加了SFP状态的新协议
            rcftTypeRC1102-E1-SLAVE-REV-B1(10131),--增加了性能统计的新协议
            rcftTypeRC1102-E1-MASTER-REV-B1(10133),--增加了性能统计的新协议
            rcftTypeRC1102-E1-SLAVE-BL-REV-A1(10136),--增加了性能统计的新协议
            rcftTypeRC1102-E1-MASTER-BL-REV-A1(10137),--增加了性能统计的新协议
            rcftTypeRC602-GE-SLAVE-REV-B(10138),
            rcftTypeRC602-GE-MASTER-REV-B(10139),
            rcftTypeRC954-FE-4E1-REV-A(10141),
            rcftTypeRC954-FX-4E1-REV-A(10142),
            rcftTypeOPCOM200-OSC-REV-A(10143),
            rcftTypeOPCOM200-OTU1-REV-B(10144),
            rcftTypeRC602-GEF-REV-B-MASTER(10145),    --光口用sfp
            rcftTypeRCVS1000-801A-1DD-REV-A(10146),
            rcftTypeRCVS1000-601A-1DD-REV-A(10147),
            rcftTypeOPCOM200-OTU2-REV-B(10148),
            rcftTypeRC1102-E1-REV-B2-MASTER(10153), ---增加了G.bert
            rcftTypeRC1102-E1-REV-B2-SLAVE(10154),  ---增加了G.bert
            rcftTypeRC902-FE4E1-BL-REV-A(10159),
            rcftTypeRC802-DS3E3-REV-A(10160),
            rcftTypeRC954-FE4E1-BL-REV-A(10161),
            rcftTypeRC954-FX4E1-BL-REV-A(10162),
            rcftTypeRC902-FX4E1-REV-B(10163),
            rcftTypeRC954-2FE4E1-BL-REV-A(10164),
            rcftTypeRC954-2FE8E1-BL-REV-A(10166),
            rcftTypeOPCOM200-OLP-R-REV-A(10167),

            rcftTypeRC954-FX8E1-REV-A-MASTER(10169),
            rcftTypeRC954-FX8E1-REV-A-SLAVE(10170),

            rcftTypeRC952-FE-DS1-MASTER-REV-A(10172),
            rcftTypeRC852-30-REV-B-MASTER(10175),
            rcftTypeRC952-FE-DS3E3-F-REV-A-MASTER(10176),    ---增加了DS3E3成帧 、线路编码、传输距离
            rcftTypeRC852-30-FV35-REV-B-MASTER(10177),		--增加了V35带宽跟随
            rcftTypeRC552-GE-REV-B-MASTER(10181),
            rcftTypeRC552-GE-REV-B-SLAVE(10182),
            rcftTypeRC952-FXE1-REV-C-MASTER(10183),
            rcftTypeRC952-FEE1-REV-B-MASTER(10184),  --对应硬件b版的移动模式 ，硬件b版的其他模式同a版
            rcftTypeRC552-GE-REV-C-MASTER(10186),
            rcftTypeRC552-GE-REV-C-SLAVE(10187),
            rcftTypeRC954-FE8E1-REV-A(10188),
            rcftTypeRC952-FE-DS3E3-REV-A-MASTER(10189),
            rcftTypeRC802-DS1-REV-A-MASTER(10190),
            rcftTypeRC522E-FE-MASTER(10194),
            rcftTypeRC522E-FE-SLAVE(10197),
            rcftTypeRC904-V35FE1-E(10198),		-- RC904-V35FE1 增强型

            rcftTypeRC552-FE-REV-B-MASTER(10201),
            rcftTypeRC552-FE-REV-B-SLAVE(10203),

            rcftTypeRC954-FE-4E1-REV-A-SLAVE(11013),
            rcftTypeRC954-FX-4E1-REV-A-SLAVE(11014),
            rcftTypeRC952-FE-DS3E3-REV-A-SLAVE(11022),
            rcftTypeRC802-DS1-REV-A-SLAVE(11023),
            rcftTypeRC952-FE-DS1-REV-A-SLAVE(11024),
            rcftTypeRC952-FE-DS3E3-F-REV-A-SLAVE(11026),	---增加了DS3E3成帧、线路编码、传输距离
            rcftTypeRC852-30-REV-B-SLAVE(11028),
            rcftTypeRC602E-GE-MASTER(11031),		--RC602E-E 虚拟设备类型
            rcftTypeRC602E-GE-SLAVE(11032),
            rcftTypeRC954-2FE4E1-BL-REV-A-SLAVE(12015),
            rcftTypeRC954-FE4E1-BL-REV-A-SLAVE(12016),
            rcftTypeRC954-FX4E1-BL-REV-A-SLAVE(12017),
            rcftTypeRC954-2FE8E1-BL-REV-A-SLAVE(12018),
            rcftTypeRC802-DS3E3-REV-A-SLAVE(12019),
            rcftTypeRC954-FE8E1-REV-A-SLAVE(12020),


            rcftTypeRC832-30-REV-A-MASTER(13055),
            rcftTypeRC832-30-FV35-REV-A-MASTER(13056),
            rcftTypeRC832-60-REV-A-MASTER(13057),
            rcftTypeRC832-120L-REV-A-MASTER(13058),
            rcftTypeRC832-240L-REV-A-MASTER(13059),
            rcftTypeRCMS2802-30FE-REV-A-MASTER(13065),
            rcftTypeRCMS2802-60FE-REV-A-MASTER(13066),
            rcftTypeRCMS2802-120LFE-REV-A-MASTER(13070),
            rcftTypeRCMS2802-240LFE-REV-A-MASTER(13071),
            rcftTypeRC832-30-FV35-REV-B-MASTER(13072),
            rcftTypeRC804-30B-S1-REV-A-MASTER(13073),
            rcftTypeRC806-30B-S1-REV-A-MASTER(13074),
            rcftTypeRC832-30-FV35-REV-A1-MASTER(13075),
            rcftTypeRCMS2802-2T1-FE-REV-A(13081),
            rcftTypeRCMS2802-4T1-FE-REV-A(13082),
            rcftTypeRCMS2802-8T1-FE-REV-A(13083),
            rcftTypeRCMS2802-60FX-REV-A(13084),

            rcftTypeRC1102-FE-REV-B-MASTER(15001),
            rcftTypeRC1102-FE-4W-REV-A-MASTER(15003),
            rcftTypeRC1102-FE-REV-B-SLAVE(15005),
            rcftTypeRC1102-FE-4W-REV-A-SLAVE(15006),

            rcftTypeRCMS2802-120LGE-BL-REV-A-MASTER(17008),
            rcftTypeRCMS2802-240LGE-BL-REV-A-MASTER(17011),
            rcftTypeRCMS2802-60GE-BL-REV-A-MASTER(17099),
            rcftTypeRCMS2802-30GE-BL-REV-A-MASTER(17100),

            rcftTypeRCMS2802-120LGE-BL-REV-A-SLAVE(18008),
            rcftTypeRCMS2802-240LGE-BL-REV-A-SLAVE(18011),
            rcftTypeRCMS2802-60GE-BL-REV-A-SLAVE(18099),
            rcftTypeRCMS2802-30GE-BL-REV-A-SLAVE(18100),

            rcftTypeRCVS1000-601BL(162468), 	---对应设备类型0xf404
            rcftTypeRCVS1000-602BL(162467),   ---对应设备类型0xf403
            rcftTypeRCVS1000-604AL(162466),   ---对应设备类型0xf402

            rcftTypeRCMS2802-60GE-BL-REV-B-MASTER(62469),   ---对应设备类型0xf405
            rcftTypeRCMS2802-60GE-BL-REV-B-SLAVE(62470),   ---对应设备类型0xf406

            rcftTypeRC904-PE1-MSTER(62512), 	---对应设备类型0xf430
            rcftTypeRC904-PE1-SLAVE(62513),   ---对应设备类型0xf431

            rcftTypeRCMS2802-120LGE-BL-REV-B-MASTER(62516),   ---对应设备类型0xf434
            rcftTypeRCMS2802-120LGE-BL-REV-B-SLAVE(62517),   ---对应设备类型0xf435

            rcftTypeRCMS2802-240LGE-BL-REV-B-MASTER(62519),   ---对应设备类型0xf437
            rcftTypeRCMS2802-240LGE-BL-REV-B-SLAVE(62520),   ---对应设备类型0xf438

            rcftTypeRC958-FE4E1-REV-A-Master(62523),     ---对应设备类型0xF43B
			rcftTypeRC958-FE4E1-REV-A-SLAVE(62525),       ---对应设备类型0xF43D
			rcftTypeRC958-FE8E1-REV-A-MASTER(62527),      ---对应设备类型0xF43F
			rcftTypeRC958-FE8E1-REV-A-SLAVE(62528),        ---对应设备类型0xF440
			rcftTypeRC958-FX4E1-REV-A-MASTER(62530),       ---对应设备类型0xF442
			rcftTypeRC958-FX4E1-REV-A-SLAVE(62531),        ---对应设备类型0xF443
			rcftTypeRC958-FX8E1-REV-A-MASTER(62534),       ---对应设备类型0xF446
			rcftTypeRC958-FX8E1-REV-A-SLAVE(62535),        ---对应设备类型0xF447
			rcftTypeRC908-FEV35-REV-A-MASTER(62537),	---对应设备类型0xf449
			rcftTypeRC908-FEV35-REV-A-SLAVE(62538),		---对应设备类型0xf44a

			rcftTypeRC958-FEE1-REV-A-Master(62541),        ---对应设备类型0xF44D
			rcftTypeRC958-FEE1-REV-A-SLAVE(62542),         ---对应设备类型0xF44E
            rcftTypeRC958-FXE1-REV-A-MASTER(62544),        ---对应设备类型0xF450
			rcftTypeRC958-FXE1-REV-A-SLAVE(62545),         ---对应设备类型0xF451

			rcftTypeRC906G-FE4E1-MASTER(62547),		---对应设备类型0xF453
			rcftTypeRC906G-FE4E1-SLAVE(62548),		---对应设备类型0xF454
			rcftTypeRC906G-FX4E1-MASTER(62551),		---对应设备类型0xF457
			rcftTypeRC906G-FX4E1-SLAVE(62552),		---对应设备类型0xF458
			rcftTypeRC906G-FEE1-MASTER(62555),		---对应设备类型0xF45B
			rcftTypeRC906G-FEE1-SLAVE(62556),		---对应设备类型0xF45C
			rcftTypeRC906G-FXE1-MASTER(62558),		---对应设备类型0xF45E
			rcftTypeRC906G-FXE1-SLAVE(62559),		---对应设备类型0xF45F
			rcftTypeRC906G-FE8E1-MASTER(62561),		---对应设备类型0xF461
			rcftTypeRC906G-FE8E1-SLAVE(62562),		---对应设备类型0xF462
			rcftTypeRC906G-FX8E1-MASTER(62564),		---对应设备类型0xF464
			rcftTypeRC906G-FX8E1-SLAVE(62565),		---对应设备类型0xF465
            rcftTypeRC414-REV-B(62568),				---对应设备类型0xF468
            rcftTypeRCVS1000-901NL(62570),			---对应设备类型0xF46A
            rcftTypeRCVS1000-901UL(62572),			---对应设备类型0xF46C

            rcftTypeRCMS2912-4E1T1GE-REV-A-MASTER(62573),     	---对应设备类型0xF46D
            rcftTypeRCMS2912-4E1T1GE-REV-A-SLAVE(62574),     	---对应设备类型0xF46E
            rcftTypeRCMS2912-8E1T1GE-REV-A-MASTER(62576),     	---对应设备类型0xF470
            rcftTypeRCMS2912-8E1T1GE-REV-A-SLAVE(62577),     	---对应设备类型0xF471

            rcftTypeOPCOM200_OTU1_A20(62579),					--0XF473 对应MCU 版本为A2

            rcftTypeRC952-SE1M-MASTER(62580), 	    ---对应设备类型0xF474
            rcftTypeRC952-SE1M-SLAVE(62581),        ---对应设备类型0xF475

            rcftTypeRCMS2902-120LFE-MASTER(62587),   ---对应设备类型0xF47B
            rcftTypeRCMS2902-120LFE-SLAVE(62588),    ---对应设备类型0xF47C
            rcftTypeRCMS2902-240LFE-MASTER(62590),   ---对应设备类型0xF47E
            rcftTypeRCMS2902-240LFE-SLAVE(62591),    ---对应设备类型0xF47F
            rcftTypeRCMS2902-60FE-MASTER(62593),	 ---对应设备类型0xF481
            rcftTypeRCMS2902-60FE-SLAVE(62594),      ---对应设备类型0xF482
            rcftTypeRC862-60-MASTER(62596),   		 ---对应设备类型0xF484
            rcftTypeRC862-60-SLAVE(62597),    		 ---对应设备类型0xF485
            rcftTypeRC862-30-MASTER(62601),   		 ---对应设备类型0xF489
            rcftTypeRC862-30-SLAVE(62602),    		 ---对应设备类型0xF48A

            rcftTypeRC952-CSE1M-MASTER(62604), 	    ---对应设备类型0xF48C
            rcftTypeRC952-CSE1M-SLAVE(62605),        ---对应设备类型0xF48D

            rcftTypeRCMS2912-480FE-MASTER(62609),   ---对应设备类型0xF491
            rcftTypeRCMS2912-480FE-SLAVE(62610),    ---对应设备类型0xF492
            rcftTypeRCMS2912-240FE-MASTER(62612),   ---对应设备类型0xF494
            rcftTypeRCMS2912-240FE-SLAVE(62613),    ---对应设备类型0xF495


            rcftUnknownType(999)
        }
        MAX-ACCESS read-only
        STATUS current
        DESCRIPTION
        "
             板卡类型
           An indication of the card type.
           13000-14000是给以RC7017为主芯片的光端机预留的设备类型。
           15000-16000是给收发器的约定四的局端master的设备类型。
           16000-17000是给收发器的约定四的局端slave的设备类型。
           17000-18000是给光端机的约定四的局端master的设备类型。
           18000-19000是给光端机的约定四的局端slave的设备类型。
         "
        ::= {rcftSlotStatEntry 3}

    rcftSlotFaultPass OBJECT-TYPE
        SYNTAX INTEGER
        {
            support(1),
            notSupport(2)
        }
        MAX-ACCESS read-write
        STATUS current
        DESCRIPTION
          "
          本模块的故障转移功能是否使能(1:使能,2:禁止).

          An indication of whether the local module supports fault-pass or not.
          "
        ::= {rcftSlotStatEntry 4}

    rcftSlotVLAN OBJECT-TYPE
        SYNTAX INTEGER
        {
            support(1),
            notSupport(2)
        }
        MAX-ACCESS read-write
        STATUS current
        DESCRIPTION
          "
          	本模块是否具有VLAN功能(1:有,2:没有).
          "
        ::= {rcftSlotStatEntry 5}

    rcftSlotConfigStatus OBJECT-TYPE
        SYNTAX INTEGER
        {
            normal(1),
            abnormal(2)
        }
        MAX-ACCESS read-only
        STATUS current
        DESCRIPTION
          "
          	本模块配置状态(1:正常,2:不正常).
          "
        ::= {rcftSlotStatEntry 6}

    rcftSlotELink OBJECT-TYPE
        SYNTAX INTEGER
        {
            linkup(1),
            linkdown(2)
        }
        MAX-ACCESS read-only
        STATUS current
        DESCRIPTION
          "
          本模块电口LINK状态(1:linkup, 2:linkdown).
          The object indicating the status of the electronic port.
          When the value is 1 the eletronic port link up,otherwise link down.
          "
        ::= {rcftSlotStatEntry 7}

    rcftSlotEAutoNegotiation OBJECT-TYPE
        SYNTAX INTEGER
        {
            auto(1),
            manul(2)
        }
        MAX-ACCESS read-write
        STATUS current
        DESCRIPTION
          "
          本模块电口速率协商方式(1:自协商,2:手动).
          This object indicating the negoation mode of the electronic port
          in the local module.When the value is 1 the eletronic port is
          set to auto negotiation,otherwise the eletronic port is set to manual negotiation.
          "
        ::= {rcftSlotStatEntry 8}

    rcftSlotEDuplex OBJECT-TYPE
        SYNTAX INTEGER
        {
            full-duplex(1),
            half-duplex(2),
            auto(3)
        }
        MAX-ACCESS read-write
        STATUS current
        DESCRIPTION
          "
          本模块电口双工模式(1:全双工,2:半双工,3:自动).
          The duplex mode of the electronic port.
          1:full duplex
          2:half duplex
          3:auto (private define and will be omitted in the future)

          "
        ::= {rcftSlotStatEntry 9}

    rcftSlotECollCount OBJECT-TYPE
        SYNTAX INTEGER
        {
            exist(1),
            notExist(2)
        }
        MAX-ACCESS read-only
        STATUS current
        DESCRIPTION
          "
          	本模块电口碰撞统计(0-65535,代表1秒内的碰撞次数L).
          "
        ::= {rcftSlotStatEntry 10}

    rcftSlotESpeed OBJECT-TYPE
        SYNTAX INTEGER
        {
            rcft10Mbps(1),
            rcft100Mbps(2),
            rcft1000Mbps(3),
            rcft10Gbps(4),
            other(16)
        }
        MAX-ACCESS read-write
        STATUS current
        DESCRIPTION
          "
            电口的速率.
            The speed of the electronic port.
            1.10Mbps
            2.100Mbps
            3.1000Mbps
            4.10Gbps
            5.other
          "
        ::= {rcftSlotStatEntry 11}

    rcftSlotETxStatus OBJECT-TYPE
        SYNTAX INTEGER
        {
            package(1),
            noPackage(2)
        }
        MAX-ACCESS read-only
        STATUS current
        DESCRIPTION
          "
          	本模块电口TX状态(1:有包, 2:无包).
          "
        ::= {rcftSlotStatEntry 12}

    rcftSlotERxStatus OBJECT-TYPE
        SYNTAX INTEGER
        {
            package(1),
            noPackage(2)
        }
        MAX-ACCESS read-only
        STATUS current
        DESCRIPTION
          "
          	本模块电口RX状态(1:有包, 2:无包).
          "
        ::= {rcftSlotStatEntry 13}

    rcftSlotOLink OBJECT-TYPE
        SYNTAX INTEGER
        {
            linkup(1),
            linkdown(2)
        }
        MAX-ACCESS read-only
        STATUS current
        DESCRIPTION
          "
          本地单芯光模块光口LINK状态(1:linkup, 2:linkdown).
          注:RC303-4-FE(REV.G),RC202-GE,RC303-4-GE 三种板卡用该对象表示光口的link状态.
          The status of the optical port with single line in the local module:
          1:linkup
          2:linkdown
          "
        ::= {rcftSlotStatEntry 14}

    rcftSlotODuplex OBJECT-TYPE
        SYNTAX INTEGER
        {
            full-duplex(1),
            half-duplex(2),
            auto(3)
        }
        MAX-ACCESS read-only
        STATUS current
        DESCRIPTION
          "
          本模块光口双工模式(1:全双工,2:半双工,3:自动).
          The duplex mode of the optical port.
          1:full duplex
          2:half duplex
          3:auto (private design and will be omitted in the future)

          "
        ::= {rcftSlotStatEntry 15}

    rcftSlotOSpeed OBJECT-TYPE
        SYNTAX INTEGER
        {
            rcft10Mbps(1),
            rcft100Mbps(2),
            rcft1GBps(3),
            rcft10Gbps(4),
            other(16)
        }
        MAX-ACCESS read-only
        STATUS current
        DESCRIPTION
          "
           本模块光口的工作速率.
           The speed of the optical port.
            1.10Mbps
            2.100Mbps
            3.1000Mbps
            4.10Gbps
            5.other
          "
        ::= {rcftSlotStatEntry 16}

    rcftSlotOTxStatus OBJECT-TYPE
        SYNTAX INTEGER
        {
            package(1),
            noPackage(2)
        }
        MAX-ACCESS read-only
        STATUS current
        DESCRIPTION
          "
          	本模块光口TX状态(1:有包, 2:无包).
          "
        ::= {rcftSlotStatEntry 17}

    rcftSlotORxStatus OBJECT-TYPE
        SYNTAX INTEGER
        {
            package(1),
            noPackage(2)
        }
        MAX-ACCESS read-only
        STATUS current
        DESCRIPTION
          "
          	本模块光口RX状态(1:有包, 2:无包).
          "
        ::= {rcftSlotStatEntry 18}

    rcftSlotDescr OBJECT-TYPE
        SYNTAX OCTET STRING(SIZE(0..10))
        MAX-ACCESS read-write
        STATUS current
        DESCRIPTION
          "
          	模块描述
          "
        ::= {rcftSlotStatEntry 19}

    rcftSlotORLnk OBJECT-TYPE
    	SYNTAX INTEGER
    	{
    	   linkup(1),
    	   linkdown(2)
    	}
    	MAX-ACCESS read-only
    	STATUS current
    	DESCRIPTION
    	   "
    	  本模块光口接收方向的link状态(1:linkup,2:linkdown).
    	  The object indicating the status of the optical port
    	  in the receiving direction.
    	  When the value is 1 the optical port link up,otherwise link down.
    	   "
        ::={rcftSlotStatEntry 20}

    rcftSlotOTLnk OBJECT-TYPE
    	SYNTAX INTEGER
    	{
    	   linkup(1),
    	   linkdown(2)
    	}
    	MAX-ACCESS read-only
    	STATUS current
    	DESCRIPTION
    	   "
    	  本模块光口发送方向的link状态(1:linkup,2:linkdown).
    	  The object indicating the status of the optical port
    	  in the transmitting direction.
    	  When the value is 1 the optical port links up,otherwise links down.
    	   "
        ::={rcftSlotStatEntry 21}

    rcftSlotORmd OBJECT-TYPE
    	SYNTAX INTEGER
    	{
    	   package(1),
    	   nopackage(2)
    	}
    	MAX-ACCESS read-only
    	STATUS current
    	DESCRIPTION
    	   "
    	   	远端模块是否有故障(1:无,2:有).
    	   "
        ::={rcftSlotStatEntry 22}

    rcftSlotOFxAct OBJECT-TYPE
    	SYNTAX INTEGER
    	{
    	   package(1),
    	   nopackage(2)
    	}
    	MAX-ACCESS read-only
    	STATUS current
    	DESCRIPTION
    	   "
    	   	本模块光口的ACT状态(1:有包,2:无包).
    	   "
        ::={rcftSlotStatEntry 23}

    rcftSlotETxAct OBJECT-TYPE
    	SYNTAX INTEGER
    	{
    	   package(1),
    	   nopackage(2)
    	}
    	MAX-ACCESS read-only
    	STATUS current
    	DESCRIPTION
    	   "
    	   	本模块电口的ACT状态(1:有包,2:无包).
    	   "
        ::={rcftSlotStatEntry 24}

    rcftSlotRemManage OBJECT-TYPE
        SYNTAX INTEGER
        {
           manage-enable(1),
           manage-disable(2)
        }
        MAX-ACCESS read-write
        STATUS current
        DESCRIPTION
        "
  	     本模块远端管理功能是否使能:(1:使能,2:禁止).
  	     An indication of whether the local module supports remote management.
  	     1: support
  	     2: not support
        "
        ::={rcftSlotStatEntry 25}

	rcftSlotLBKTest OBJECT-TYPE
        SYNTAX INTEGER
        {
           loopbacktest-enable(1),
           loopbacktest-disable(2)
        }
        MAX-ACCESS read-only
        STATUS current
        DESCRIPTION
          "
          本模块是否处于光口环回测试方式.
          当发送了环回命令后,通过察看该对象的状态判断单片机是否执行了环回测试命令.
          After sending the order by setting  the object of the rcftSlotOrder to 1
          we can see whether the mcu excute the command through the value of this object
          -- rcftSlotLBKTest :
          1: mcu has excuted the instruction and the loop-test is enabled
          2: mcu hasn't excuted the instruction and the loop-test is still disabled

          "
        ::={rcftSlotStatEntry 26}

    rcftSlotVOLimit OBJECT-TYPE
        SYNTAX INTEGER
        {
           normal(1),
           voltageoverlimit(2)
        }
        MAX-ACCESS read-only
        STATUS current
        DESCRIPTION
          "
          	本模块供电电压是否超过所固定的上限值:(1:正常,2:超过).
          "
        ::={rcftSlotStatEntry 27}

    rcftSlotVBLimit OBJECT-TYPE
        SYNTAX INTEGER
        {
           normal(1),
           voltagebelowlimit(2)
        }
        MAX-ACCESS read-only
        STATUS current
        DESCRIPTION
          "
          	本模块供电电压是否超过所固定的下限值:(1:正常,2:超过).
          "
        ::={rcftSlotStatEntry 28}

   rcftSlotLBKTestOk OBJECT-TYPE
       SYNTAX INTEGER
       {
          loopbacktestok(1),
          loopbacktestfault(2)
       }
       MAX-ACCESS read-only
       STATUS current
       DESCRIPTION
         "
          本模块光口环回测试执行结果(1:成功,2:失败).
          当发送环回命令后,通过察看该对象的状态判断环回命令执行的结果
          The value of this object show the result of the loop test.
          After sending the order by setting the object of the rcftSlotOrder to 1
          two thing should be done:
          first -- judge whether the mcu excute the instruction throug the value
          of the rcftSlotLBKTest above.
          secondly -- if the condition above is true then judge the result of the
          loop test throug the value of this object:
          1: loop test ok
          2: loop test fault

         "
       ::={rcftSlotStatEntry 29}

   rcftSlotEPort OBJECT-TYPE
       SYNTAX INTEGER
       {
          open(1),
          close(2)
       }
       MAX-ACCESS read-write
       STATUS current
       DESCRIPTION
       "
         本模块电口开关使能:(1:打开,2关闭).
         Open or close the electronic port in the local module.
       "
       ::={rcftSlotStatEntry 30}

   rcftSlotOSendPower OBJECT-TYPE
       SYNTAX INTEGER
       {
          normal(1),
          abnormal(2)
       }
       MAX-ACCESS read-only
       STATUS current
       DESCRIPTION
       "
        	本模块发送光功率是否正常:(1:正常,2:异常).
       "
       ::={rcftSlotStatEntry 31}

   rcftSlotOReceSen OBJECT-TYPE
       SYNTAX INTEGER
       {
          normal(1),
          abnormal(2)
       }
       MAX-ACCESS read-only
       STATUS current
       DESCRIPTION
       "
         	本模块接收灵敏度是否正常:(1:正常,2:异常).
       "
       ::={rcftSlotStatEntry 32}

   rcftSlotOLaser OBJECT-TYPE
       SYNTAX INTEGER
       {
          normal(1),
          abnormal(2)
       }
       MAX-ACCESS read-only
       STATUS current
       DESCRIPTION
       "
         	本模块激光管工作是否正常:(1:正常,2:异常).
       "
       ::={rcftSlotStatEntry 33}

   rcftSlotOSD OBJECT-TYPE
       SYNTAX INTEGER
       {
          normal(1),
          abnormal(2)
       }
       MAX-ACCESS read-only
       STATUS current
       DESCRIPTION
       "
         本地光模块的SD输出信号是否正常:(1:正常,2:异常).
         Showing the SD output signal of the local optical module is normal or not.
       "
       ::={rcftSlotStatEntry 34}

   rcftSlotOPort OBJECT-TYPE
       SYNTAX INTEGER
       {
          open(1),
          close(2)
       }
       MAX-ACCESS read-write
       STATUS current
       DESCRIPTION
         "
         局端模块光口开关使能:(1:打开,2关闭).
         Open or close the optical port in the local module.

         "
       ::={rcftSlotStatEntry 35}

  rcftSlotOrder OBJECT-TYPE
      SYNTAX INTEGER
      {
         localreset(1),
         olooptestenable(2),
         olooptestdisable(3),
		 v35looptestenable(4),
		 v35looptestdisable(5),
		 e1port1remotelooptestenable(6),
		 e1port1remotelooptestdisable(7),
		 e1locallooptestenable(8),
		 e1locallooptestdisable(9),
		 v35remotelooptestenable(10),
		 v35remotelooptestdisable(11),
		 e1port2remotelooptestenable(12),
		 e1port2remotelooptestdisable(13),
		 eltwoportremotelooptestenable(14),
		 e1twoportremotelooptestdisable(15),
		 resetLocalEthPort(16),
		 resetRemoteEthPort(17),
		 resetLocalRemoteEthPort(18),
		 allE1RemoteLoop(19),
		 allE1RemoteNormal(20),
		 localInsideLoopEnable(21),
		 localInsideLoopDisable(22),
		 remoteOutsideLoopEnable(23),
		 remoteOutsideLoopDisable(24),
		 localDoubleLoopEnable(25),
		 localDoubleLoopDisable(26),
		 cwdmClientLoopEnable(27),
		 cwdmClientLoopDisable(28),
	     cwdmLineLoopEnable(29),
	     cwdmLineLoopDisable(30),
		 cwdmcdrReset(31),
		 e1port1DoubleLoopEnable(32),
		 e1port2DoubleLoopEnable(33),
		 startRequestInfo(34),
		 stopRequestInfo(35),
		 errCodeFunctionOpen(36),
		 errCodeFunctionClose(37),
		 remoteDoubleLoopDisable(38),
		 linePortInsideLoopEnable(39),
		 linePortOutsideLoopEnable(40),
		 linePortInsideLoopDisable(41),
		 linePortOutsideLoopDisable(42),
		 remoteInsideLoopEnable(43),
		 remoteInsideLoopDisable(44),

		 e1port1OutsideLoopEnable(45),
		 e1port2OutsideLoopEnable(46),
		 e1port3OutsideLoopEnable(47),
		 e1port4OutsideLoopEnable(48),
		 allE1OutsideLoopEnable(49),
		 allE1OutsideLoopDisable(50),

		 e1port1InsideLoopEnable(51),
		 e1port2InsideLoopEnable(52),
		 e1port3InsideLoopEnable(53),
		 e1port4InsideLoopEnable(54),
		 allE1InsideLoopEnable(55),
		 allE1InsideLoopDisable(56),

		 opticalRateAjustEnable(57),
         opticalRateAjustDisable(58),

		 e1port1OutsideLoopDisable(59),
		 e1port2OutsideLoopDisable(60),
		 e1port3OutsideLoopDisable(61),
		 e1port4OutsideLoopDisable(62),

		 remotee1port1OutsideLoopEnable(63),
		 remotee1port2OutsideLoopEnable(64),
		 remotee1port3OutsideLoopEnable(65),
		 remotee1port4OutsideLoopEnable(66),
		 remoteallE1OutsideLoopEnable(67),

		 remotee1port1OutsideLoopDisable(68),
		 remotee1port2OutsideLoopDisable(69),
		 remotee1port3OutsideLoopDisable(70),
		 remotee1port4OutsideLoopDisable(71),
		 remoteallE1OutsideLoopDisable(72),

		 e1port1errCodeFunctionOpen(73),
		 e1port2errCodeFunctionOpen(74),
		 e1port3errCodeFunctionOpen(75),
		 e1port4errCodeFunctionOpen(76),
		 allE1errCodeFunctionOpen(77),

		 e1port1errCodeFunctionClose(78),
		 e1port2errCodeFunctionClose(79),
		 e1port3errCodeFunctionClose(80),
		 e1port4errCodeFunctionClose(81),
		 allE1errCodeFunctionClose(82),
		 remoteE1Port1InsideLoopEnable(83),
		 remoteE1Port2InsideLoopEnable(84),
		 remoteE1Port3InsideLoopEnable(85),
		 remoteE1Port4InsideLoopEnable(86),
		 remoteAllE1InsideLoopEnable(87),
		 remoteE1Port1InsideLoopDisable(88),
		 remoteE1Port2InsideLoopDisable(89),
		 remoteE1Port3InsideLoopDisable(90),
		 remoteE1Port4InsideLoopDisable(91),
		 remoteAllE1InsideLoopDisable(92),

		 --5-8 路E1外环使能
		 e1port5OutsideLoopEnable(93),
		 e1port6OutsideLoopEnable(94),
		 e1port7OutsideLoopEnable(95),
		 e1port8OutsideLoopEnable(96),
		 --5-8 路E1外环禁止
		 e1port5OutsideLoopDisable(97),
		 e1port6OutsideLoopDisable(98),
		 e1port7OutsideLoopDisable(99),
		 e1port8OutsideLoopDisable(100),
		  --5-8 路远端E1外环使能
		 remotee5port1OutsideLoopEnable(101),
		 remotee6port2OutsideLoopEnable(102),
		 remotee7port3OutsideLoopEnable(103),
		 remotee8port4OutsideLoopEnable(104),
		  --5-8 路远端E1外环禁止
		 remotee5port1OutsideLoopDisable(105),
		 remotee6port2OutsideLoopDisable(106),
		 remotee7port3OutsideLoopDisable(107),
		 remotee8port4OutsideLoopDisable(108),
		 --5-8 路E1误码仪功能使能
		 e1port5errCodeFunctionOpen(109),
		 e1port6errCodeFunctionOpen(110),
		 e1port7errCodeFunctionOpen(111),
		 e1port8errCodeFunctionOpen(112),
		 --5-8 路E1误码仪功能禁止
		 e1port5errCodeFunctionClose(113),
		 e1port6errCodeFunctionClose(114),
		 e1port7errCodeFunctionClose(115),
		 e1port8errCodeFunctionClose(116),

		 e1UnUsedAlarmMask(117),
		 e1UnUsedAlarmUnMask(118),

		 localStatisticsClear(119)
      }
      MAX-ACCESS read-write
      STATUS current
      DESCRIPTION
      "
        局端模块的命令字(1:复位,2:环回使能,3:环回禁止,
                          34:开始强制查询本端模块的状态信息,
                          35:停止强制查询本端模块的状态信息).
        每一种板卡都有自己固定的命令字,通过发送命令执行某种操作.
        注:开始进行流量统计时要发送34:开始强制查询本端模块的状态信息
        	结束流量统计时要发送命令35:停止强制查询本端模块的状态信息
        	其它情况下无需发送该命令
        Every card has its several fixed order.

	 	-------------------------------------------
	 	  |  bit31-27  |   bit26-22 |      bit21-0    |
	 	-------------------------------------------
	 	  |端口类型  	|    端口ID  |   命令字        |
	 	-------------------------------------------
	 	约定：
	 	端口类型有5位：
	 	        0： 表示设备
	 			1	以太网电口
	 	2	以太网光口
	 	3	G.SHDSL端口
	 	4	E1端口(Sa比特不处理)
	 	5	V35端口
	 	端口ID有5位：0-31表示32个端口
	 	命令字有22位：
	 	  1：硬复位
	 	  2：软复位
	 	  3：开始查询统计信息
	 	  4：结束查询统计信息
	 	  5：内环使能        ---20090819 以后不再使用此枚举，统一采用下面的枚举
	 	  6：内环禁止        ---20090819 以后不再使用此枚举，统一采用下面的枚举
	 	  7：外环使能        ---20090819 以后不再使用此枚举，统一采用下面的枚举
	 	  8：外环禁止        ---20090819 以后不再使用此枚举，统一采用下面的枚举
	 	  9：无环回          ---20090819 以后不再使用此枚举，统一采用下面的枚举
	 	  10：本地内环使能
	 	  11：本地外环使能
	 	  12：本地双向环使能
	 	  13：远端内环使能
	 	  14：远端外环使能
	 	  15：远端双向环使能
	 	  16：本地内环禁止
	 	  17：本地外环禁止
	 	  18：本地双向环禁止
	 	  19：远端内环禁止
	 	  20：远端外环禁止
	 	  21：远端双向环禁止
 		  22: 端口BERT测试开始
 		  23: 端口BERT测试结束

	 注意：对于约定四而言，使用rcftSlotOrder作为内部变量，按照上面的格式将设备级的命令和
	 端口级的命令转化为一个字符串、综合处理。因此，这就要求rcftSlotOrder的枚举值要和各个
	 接口级命令的枚举值完全一致。如果某个接口级的命令添加了一个新的枚举值，就要把其他接口
	 下的命令和rcftSlotOrder的枚举值都添加一下。总之，要做到一改全改、始终一致。
      "
      ::={rcftSlotStatEntry 36}

    rcftRSlotExist OBJECT-TYPE
        SYNTAX INTEGER
        {
            exist(1),
            notExist(2)
        }
        MAX-ACCESS read-only
        STATUS current
        DESCRIPTION
          "
          远端槽位板卡存在状态(1:存在,2:不存在). 当以rcftSlotIndex为索引的槽位不存在远端
          板卡时该槽位关于远端板卡的所有对象没有意义,其值被清零.
          The value of this object indicates whether the card inserted in the slot whose index
          is rcftSlotIndex has its remote card.When there is no remote card
          the objects for the remote module in the rcftSlotStatTable except for
          rcftRSlotExist are meaningless and their value is 0.

          "
        ::= {rcftSlotStatEntry 37}

  rcftRSlotEAutoNegotiation OBJECT-TYPE
      SYNTAX INTEGER
      {
          auto(1),
          manul(2)
      }
      MAX-ACCESS read-write
      STATUS current
      DESCRIPTION
        "
        远端模块电口速率协商方式(1:自协商,2:手动).
        This object indicating the negoation mode of the electronic port
        in the remote module.When the value is 1 the eletronic port is
        set to auto negotiation,otherwise the eletronic port is set to manual negotiation.

        "
      ::= {rcftSlotStatEntry 38}

  rcftRSlotEDuplex OBJECT-TYPE
      SYNTAX INTEGER
      {
          full-duplex(1),
          half-duplex(2),
          auto(3)
      }
      MAX-ACCESS read-write
      STATUS current
      DESCRIPTION
        "
          远端模块电口双工模式(1:全双工,2:半双工,3:自动).
          The duplex mode of the electronic port in the remote module.
          1:full duplex
          2:half duplex
          3:auto (private define and will be omitted in the future)
        "
      ::= {rcftSlotStatEntry 39}

  rcftRSlotELink OBJECT-TYPE
      SYNTAX INTEGER
      {
          linkup(1),
          linkdown(2)
      }
      MAX-ACCESS read-only
      STATUS current
      DESCRIPTION
        "
        远端模块电口的LINK状态(1:linkup, 2:linkdown).
        The object indicating the status of the electronic port in the remote module.
        When the value is 1 the eletronic port link up,otherwise link down.

        "
      ::= {rcftSlotStatEntry 40}

  rcftRSlotFaultPass OBJECT-TYPE
      SYNTAX INTEGER
      {
          support(1),
          notSupport(2)
      }
      MAX-ACCESS read-write
      STATUS current
      DESCRIPTION
        "
       	 远端模块线路故障转移功能是否使能(1:使能,2:不使能).
       	 An indication of whether the remote module supporting fault-pass.
        "
        ::= {rcftSlotStatEntry 41}

  rcftRSlotEPort OBJECT-TYPE
      SYNTAX INTEGER
      {
          open(1),
          close(2)
      }
      MAX-ACCESS read-write
      STATUS current
      DESCRIPTION
        "
       	 远端模块电口开关是否打开:(1:打开,2关闭).
       	 Open or close the electronic port in the remote module.
        "
      ::={rcftSlotStatEntry 42}

   rcftRSlotRemManage OBJECT-TYPE
       SYNTAX INTEGER
       {
          manage-enable(1),
          manage-disable(2)
       }
       MAX-ACCESS read-write
       STATUS current
       DESCRIPTION
       "
       	 远端模块是否具有被管理功能:(1:使能,2:禁止         ).
       "
       ::={rcftSlotStatEntry 43}

   rcftRSlotVOLimit OBJECT-TYPE
      SYNTAX INTEGER
      {
         normal(1),
         voltageoverlimit(2)
      }
      MAX-ACCESS read-only
      STATUS current
      DESCRIPTION
      "
        	远端模块供电电压是否超过所固定的上限值:(1:正常,2:超过).
      "
      ::={rcftSlotStatEntry 44}

    rcftRSlotVBLimit OBJECT-TYPE
        SYNTAX INTEGER
        {
           normal(1),
           voltagebelowlimit(2)
        }
        MAX-ACCESS read-only
        STATUS current
        DESCRIPTION
        "
          	远端模块供电电压是否超过所固定的下限值:(1:正常,2:超过).
        "
        ::={rcftSlotStatEntry 45}

    rcftRSlotOSendPower OBJECT-TYPE
       SYNTAX INTEGER
       {
         normal(1),
         abnormal(2)
       }
       MAX-ACCESS read-only
       STATUS current
       DESCRIPTION
       "
         	远端模块发送光功率是否正常:(1:正常,2:异常).
       "
       ::={rcftSlotStatEntry 46}

   rcftRSlotOReceSen OBJECT-TYPE
       SYNTAX INTEGER
       {
          normal(1),
          abnormal(2)
       }
       MAX-ACCESS read-only
       STATUS current
       DESCRIPTION
       "
         	远端模块接收灵敏度是否正常:(1:正常,2:异常).
       "
       ::={rcftSlotStatEntry 47}

   rcftRSlotOLaser OBJECT-TYPE
       SYNTAX INTEGER
       {
          normal(1),
          abnormal(2)
       }
       MAX-ACCESS read-only
       STATUS current
       DESCRIPTION
       "
         	远端模块激光管工作是否正常:(1:正常,2:异常).
       "
       ::={rcftSlotStatEntry 48}

   rcftRSlotOSD OBJECT-TYPE
       SYNTAX INTEGER
       {
          normal(1),
          abnormal(2)

       }
       MAX-ACCESS read-only
       STATUS current
       DESCRIPTION
       "
         	远端模块光口SD信号是否正常:(1:正常,2:异常).
       "
       ::={rcftSlotStatEntry 49}

    rcftRSlotOLink OBJECT-TYPE
       SYNTAX INTEGER
        {
            link(1),
            unlink(2)
        }
        MAX-ACCESS read-only
        STATUS current
        DESCRIPTION
        "
          	远端模块光口LINK(1:LINK, 2:UNLINK).
        "
        ::= {rcftSlotStatEntry 50}

    rcftRSlotOrder OBJECT-TYPE
      SYNTAX INTEGER
      {
         remotereset(1),
         resetEthPort(2),
		 localInsideLoopEnable(3),
		 localInsideLoopDisable(4),
		 e1port1LocalOutsideLoopEnable(5),
		 e1port1LocalOutsideLoopDisable(6),
		 pollingTemperature(7),
		 e1port2Locallooptestenable(12),
		 e1port2Locallooptestdisable(13),
		 eltwoportLocallooptestenable(14),
		 e1twoportLocallooptestdisable(15),
		 localDoubleLoopEnable(25),
		 localDoubleLoopDisable(26),
		 e1port1DoubleLoopEnable(32),
		 e1port2DoubleLoopEnable(33),
		 requestInfoStart(34),
		 requestInfoStop(35),
		 errCodeFunctionOpen(36),
		 errCodeFunctionClose(37),
		 remoteDoubleLoopDisable(38),
		 linePortInsideLoopEnable(39),
		 linePortOutsideLoopEnable(40),
		 linePortInsideLoopDisable(41),
		 linePortOutsideLoopDisable(42),
		 localV35InsideLoopEnable(43),

		 e1port1OutsideLoopEnable(45),
		 e1port2OutsideLoopEnable(46),
		 e1port3OutsideLoopEnable(47),
		 e1port4OutsideLoopEnable(48),
		 allE1OutsideLoopEnable(49),
		 allE1OutsideLoopDisable(50),

		 e1port1InsideLoopEnable(51),
		 e1port2InsideLoopEnable(52),
		 e1port3InsideLoopEnable(53),
		 e1port4InsideLoopEnable(54),
		 allE1InsideLoopEnable(55),
		 allE1InsideLoopDisable(56),

		 saveDeviceConfig(57),
		 deleteDeviceConfig(58),
		 maskUnusedE1Alarm(59),
		 unmaskUnusedAlarm(60),
		 deviceRestart(61),
		 localE1Port1InsideLoopEnable(62),
		 localE1Port2InsideLoopEnable(63),
     	 localE1Port3InsideLoopEnable(64),
		 localE1Port4InsideLoopEnable(65),
		 localAllE1PortInsideLoopEnable(66),
		 localE1Port1InsideLoopDisable(67),
		 localE1Port2InsideLoopDisable(68),
     	 localE1Port3InsideLoopDisable(69),
		 localE1Port4InsideLoopDisable(70),
		 localAllE1PortInsideLoopDisable(71),
		 allE1PortLoopDisable(72)  -- 针对801-120B-REV.M设备指的是将本地外环和对端内环清除掉


      }
      MAX-ACCESS read-write
      STATUS current
      DESCRIPTION
      "
         远端模块的命令字.通过向远端模块发送命令字使远端模块执行相应的操作.
        remotereset(1): 使远端模块复位.
        requestInfoStart(34):开始强制查询本端模块的状态信息,
        requestInfoStop(35) :停止强制查询本端模块的状态信息).
        每一种板卡都有自己固定的命令字,通过发送命令执行某种操作.
        注:开始进行流量统计时要发送34:开始强制查询远端模块的状态信息
        	结束流量统计时要发送命令35:停止强制查询远端模块的状态信息
        	其它情况下无需发送该命令
        Every card has its several fixed order.
      "
      ::= { rcftSlotStatEntry 51 }

    rcftSlotRowStatus OBJECT-TYPE
        SYNTAX INTEGER
        {
           active (1)
        }
        MAX-ACCESS      read-write
        STATUS          current
        DESCRIPTION
        "
          该对象作为一次网管配置的结束标志.在进行配置操作时网管一次可
          以绑定若干个对象,但SNMP VB邦定的最后一个VB必须为rcftSlotRowStatus,
          且置1,以表明本次配置结束.同样在发送命令字时在绑定rcftSlotOrder或
          rcftRSlotOrder的同时要绑定rcftSlotRowStatus,且置1,以表明本次命令结束.
          Agent通过判断这个标志才能进行配置或命令操作.
        "
        ::= { rcftSlotStatEntry 52 }

    rcftRSlotType OBJECT-TYPE
        SYNTAX INTEGER
        {
            rcftTypeRC601-FE-M-REV-C(96),
            rcftTypeRC601-FE-S1-REV-C(97),
            rcftTypeRC601-FE-S2-REV-C(98),
            rcftTypeRC601-FE-S3-REV-C(99),
            rcftTypeRC501-FE-M-REV-C(108),
            rcftTypeRC501-FE-S1-REV-C(109),
            rcftTypeRC501-FE-S2-REV-C(110),
            rcftTypeRC501-FE-S3-REV-C(111),
            rcftTypeRC603-FE-M-REV-C(160),
            rcftTypeRC603-FE-S1-REV-C(161),
            rcftTypeRC603-FE-S2-REV-C(162),
            rcftTypeRC603-FE-S3-REV-C(163),
            rcftTypeRC503-FE-M-REV-C(168),
            rcftTypeRC503-FE-S1-REV-C(169),
            rcftTypeRC503-FE-S2-REV-C(170),
            rcftTypeRC503-FE-S3-REV-C(171),
            rcftTypeRC503-E-M-REV-C(176),
            rcftTypeRC503-E-S1-REV-C(177),
            rcftTypeRC503-E-S2-REV-C(178),
            rcftTypeRC503-E-S3-REV-C(179),
            rcftTypeRC605-FE-M-REV-C(212),
            rcftTypeRC605-FE-S1-REV-C(213),
            rcftTypeRC605-FE-S2-REV-C(214),
            rcftTypeRC605-FE-S3-REV-C(215),
            rcftTypeRC505-FE-M-REV-C(220),
            rcftTypeRC505-FE-S1-REV-C(221),
            rcftTypeRC505-FE-S2-REV-C(222),
            rcftTypeRC505-FE-S3-REV-C(223),
            rcftTypeRC501-E-M-REV-C(232),
            rcftTypeRC501-E-S1-REV-C(233),
            rcftTypeRC501-E-S2-REV-C(234),
            rcftTypeRC501-E-S3-REV-C(235),
            rcftTypeRC505-E-M-REV-C(244),
            rcftTypeRC505-E-S1-REV-C(245),
            rcftTypeRC505-E-S2-REV-C(246),
            rcftTypeRC505-E-S3-REV-C(247),
            rcftTypeRC511-FE-M-REV-A(308),
            rcftTypeRC511-FE-S1-REV-A(309),
            rcftTypeRC511-FE-S2-REV-A(310),
            rcftTypeRC511-FE-S3-REV-A(311),
            rcftTypeRC503-8FE-M-REV-C(316),
            rcftTypeRC503-8FE-S1-REV-C(317),
            rcftTypeRC503-8FE-S2-REV-C(318),
            rcftTypeRC503-8FE-S3-REV-C(319),
            rcftTypeRC513-FE-M-REV-A(324),
            rcftTypeRC513-FE-S1-REV-A(325),
            rcftTypeRC513-FE-S2-REV-A(326),
            rcftTypeRC513-FE-S3-REV-A(327),
            rcftTypeRC501-8FE-M-REV-C(352),
            rcftTypeRC501-8FE-S1-REV-C(353),
            rcftTypeRC501-8FE-S2-REV-C(354),
            rcftTypeRC501-8FE-S3-REV-C(355),
            rcftTypeRC501-16FE-M-REV-C(356),
            rcftTypeRC501-16FE-S1-REV-C(357),
            rcftTypeRC501-16FE-S2-REV-C(358),
            rcftTypeRC501-16FE-S3-REV-C(359),
            rcftTypeRC503-16FE-M-REV-C(364),
            rcftTypeRC503-16FE-S1-REV-C(365),
            rcftTypeRC503-16FE-S2-REV-C(366),
            rcftTypeRC503-16FE-S3-REV-C(367),
            rcftTypeRC501-8FE-M-REV-C1(384),
            rcftTypeRC501-8FE-S1-REV-C1(385),
            rcftTypeRC501-8FE-S2-REV-C1(386),
            rcftTypeRC501-8FE-S3-REV-C1(387),
            rcftTypeRC501-16FE-M-REV-C1(388),
            rcftTypeRC501-16FE-S1-REV-C1(389),
            rcftTypeRC501-16FE-S2-REV-C1(390),
            rcftTypeRC501-16FE-S3-REV-C1(391),
            rcftTypeRC503-8FE-M-REV-C1(392),
            rcftTypeRC503-8FE-S1-REV-C1(393),
            rcftTypeRC503-8FE-S2-REV-C1(394),
            rcftTypeRC503-8FE-S3-REV-C1(395),
            rcftTypeRC503-16FE-M-REV-C1(396),
            rcftTypeRC503-16FE-S1-REV-C1(397),
            rcftTypeRC503-16FE-S2-REV-C1(398),
            rcftTypeRC503-16FE-S3-REV-C1(399),

            rcftTypeRemote-RC512-FE-M-REV-A-SLAVE(420),
            rcftTypeRemote-RC512-FE-S1-REV-A-SLAVE(421),
            rcftTypeRemote-RC512-FE-S2-REV-A-SLAVE(422),
            rcftTypeRemote-RC512-FE-S3-REV-A-SLAVE(423),

            rcftTypeRC801-30B-FV35-M-REV-M(472),
            rcftTypeRC801-30B-FV35-S1-REV-M(473),
            rcftTypeRC801-30B-FV35-S2-REV-M(474),
            rcftTypeRC801-30B-FV35-S3-REV-M(475),
            rcftTypeRC805-30B-FV35-M-REV-M(484),
            rcftTypeRC805-30B-FV35-S1-REV-M(485),
            rcftTypeRC805-30B-FV35-S2-REV-M(486),
            rcftTypeRC805-30B-FV35-S3-REV-M(487),
            rcftTypeRC511-FE-M-C-REV-A(492),
            rcftTypeRC511-FE-S1-C-REV-A(493),
            rcftTypeRC511-FE-S2-C-REV-A(494),
            rcftTypeRC511-FE-S3-C-REV-A(495),
            rcftTypeRC513-FE-M-C-REV-A(496),
            rcftTypeRC513-FE-S1-C-REV-A(497),
            rcftTypeRC513-FE-S2-C-REV-A(498),
            rcftTypeRC513-FE-S3-C-REV-A(499),
            rcftTypeRC601-FE-M-REV-E(504),
            rcftTypeRC601-FE-S1-REV-E(505),
            rcftTypeRC601-FE-S2-REV-E(506),
            rcftTypeRC601-FE-S3-REV-E(507),
            rcftTypeRC515-FE-M-REV-A(528),
            rcftTypeRC515-FE-S1-REV-A(529),
            rcftTypeRC515-FE-S2-REV-A(530),
            rcftTypeRC515-FE-S3-REV-A(531),
            rcftTypeRC603-FE-M-REV-E(552),
            rcftTypeRC603-FE-S1-REV-E(553),
            rcftTypeRC603-FE-S2-REV-E(554),
            rcftTypeRC603-FE-S3-REV-E(555),
            rcftTypeRC605-FE-M-REV-E(560),
            rcftTypeRC605-FE-S1-REV-E(561),
            rcftTypeRC605-FE-S2-REV-E(562),
            rcftTypeRC605-FE-S3-REV-E(563),

            rcftTypeRemote-RC512-FE-noOptical1-SLAVE(612),
            rcftTypeRemote-RC512-FE-SS13-SLAVE(613),
            rcftTypeRemote-RC512-FE-SS23-SLAVE(614),
            rcftTypeRemote-RC512-FE-SS34-SLAVE(615),      --对应于RC512-FE-SLAVE（局端slave）

            rcftTypeRC801-60B-FV35-M-REV-M(632),
            rcftTypeRC801-60B-FV35-S1-REV-M(633),
            rcftTypeRC801-60B-FV35-S2-REV-M(634),
            rcftTypeRC801-60B-FV35-S3-REV-M(635),
            rcftTypeRC805-60B-FV35-M-REV-M(636),
            rcftTypeRC805-60B-FV35-S1-REV-M(637),
            rcftTypeRC805-60B-FV35-S2-REV-M(638),
            rcftTypeRC805-60B-FV35-S3-REV-M(639),
            rcftTypeRC801-30B-FV35-REV-N(696),
     		rcftTypeRC803-30B-FV35-REV-N(700),
     		rcftTypeRC805-30B-FV35-REV-N(704),
            rcftTypeRC801-60B-FV35-REV-N(708),
     		rcftTypeRC803-60B-FV35-REV-N(712),
     		rcftTypeRC805-60B-FV35-REV-N(716),
     	    rcftTypeRC601-FE-C-M-REV-E(724),
     		rcftTypeRC601-FE-C-S1-REV-E(725),
     		rcftTypeRC601-FE-C-S2-REV-E(726),
     		rcftTypeRC601-FE-C-S3-REV-E(727),

     		rcftTypeRC512-FE-S-M-REV-A(732),
     		rcftTypeRC512-FE-S-S1-REV-A(733),
     		rcftTypeRC512-FE-S-S2-REV-A(734),
     		rcftTypeRC512-FE-S-S3-REV-A(735),

     		rcftTypeRC512-FE-S-noOptical1-REV-A(736),    --当硬件的拨码无意义时显示成这样
     		rcftTypeRC512-FE-S-SS13-REV-A(737),
     		rcftTypeRC512-FE-S-SS23-REV-A(738),
     		rcftTypeRC512-FE-S-SS34-REV-A(739),

     		rcftTypeRC512-FE-C-M-REV-A(744),
     		rcftTypeRC512-FE-C-S1-REV-A(745),
     		rcftTypeRC512-FE-C-S2-REV-A(746),
     		rcftTypeRC512-FE-C-S3-REV-A(747),

     		rcftTypeRC512-FE-C-noOptical1-REV-A(748),      --当硬件的拨码无意义时显示成这样
     		rcftTypeRC512-FE-C-SS13-REV-A(749),
     		rcftTypeRC512-FE-C-SS23-REV-A(750),
     		rcftTypeRC512-FE-C-SS34-REV-A(751),

     		rcftTypeRC512-FE(808),  --对于B版以前未处理的光头类型统一占用的类型号(0xbb+0xf)*4 送给网管，占用的是0xbb(假号)
	    	rcftTypeRC512-FE-SLAVE(740), --对于B版以前未处理的光头类型统一占用的类型号(0xaa+0xf)*4 送给网管，占用的是0xaa(假号)

	    	rcftTypeRC902-FE4E1-REV-A(60),
	    	rcftTypeRC901-FE4E1-REV-D(68),
	    	rcftTypeRC901-FE4E1-REV-B(120),
        	rcftTypeRC901(720),
            rcftTypeRCMS2201-30-M-REV-A(1000),
            rcftTypeRCMS2201-30-S1-REV-A(1001),
            rcftTypeRCMS2201-30-S2-REV-A(1002),
            rcftTypeRCMS2201-30-S3-REV-A(1003),
            rcftTypeRCMS2401-30-M-REV-A(1004),
            rcftTypeRCMS2401-30-S1-REV-A(1005),
            rcftTypeRCMS2401-30-S2-REV-A(1006),
            rcftTypeRCMS2401-30-S3-REV-A(1007),
            rcftTypeRCMS2601-30-M-REV-A(1008),
            rcftTypeRCMS2601-30-S1-REV-A(1009),
            rcftTypeRCMS2601-30-S2-REV-A(1010),
            rcftTypeRCMS2601-30-S3-REV-A(1011),
            rcftTypeRCMS2101-30-FV35-M-REV-A(1012),
            rcftTypeRCMS2101-30-FV35-S1-REV-A(1013),
            rcftTypeRCMS2101-30-FV35-S2-REV-A(1014),
            rcftTypeRCMS2101-30-FV35-S3-REV-A(1015),
            rcftTypeRCMS2501-30-FV35-M-REV-A(1016),
            rcftTypeRCMS2501-30-FV35-S1-REV-A(1017),
            rcftTypeRCMS2501-30-FV35-S2-REV-A(1018),
            rcftTypeRCMS2501-30-FV35-S3-REV-A(1019),
            rcftTypeRCMS2201-60-M-REV-A(1020),
            rcftTypeRCMS2201-60-S1-REV-A(1021),
            rcftTypeRCMS2201-60-S2-REV-A(1022),
            rcftTypeRCMS2201-60-S3-REV-A(1023),
            rcftTypeRCMS2401-60-M-REV-A(1024),
            rcftTypeRCMS2401-60-S1-REV-A(1025),
            rcftTypeRCMS2401-60-S2-REV-A(1026),
            rcftTypeRCMS2401-60-S3-REV-A(1027),
            rcftTypeRCMS2601-60-M-REV-A(1028),
            rcftTypeRCMS2601-60-S1-REV-A(1029),
            rcftTypeRCMS2601-60-S2-REV-A(1030),
            rcftTypeRCMS2601-60-S3-REV-A(1031),
            rcftTypeRC802-30-G703-M-REV-M(1032),
	    rcftTypeRC802-30-G703-S1-REV-M(1033),
	    rcftTypeRC802-30-G703-S2-REV-M(1034),
	    rcftTypeRC802-30-G703-S3-REV-M(1035),
            rcftTypeRC804-30-G703-M-REV-M(1036),
	    rcftTypeRC804-30-G703-S1-REV-M(1037),
	    rcftTypeRC804-30-G703-S2-REV-M(1038),
	    rcftTypeRC804-30-G703-S3-REV-M(1039),
            rcftTypeRC806-30-G703-M-REV-M(1040),
	    rcftTypeRC806-30-G703-S1-REV-M(1041),
	    rcftTypeRC806-30-G703-S2-REV-M(1042),
	    rcftTypeRC806-30-G703-S3-REV-M(1043),
            rcftTypeRC802-30B-FV35-M-REV-M(1044),
            rcftTypeRC802-30B-FV35-S1-REV-M(1045),
            rcftTypeRC802-30B-FV35-S2-REV-M(1046),
            rcftTypeRC802-30B-FV35-S3-REV-M(1047),
            rcftTypeRC804-30B-FV35-M-REV-M(1048),
            rcftTypeRC804-30B-FV35-S1-REV-M(1049),
            rcftTypeRC804-30B-FV35-S2-REV-M(1050),
            rcftTypeRC804-30B-FV35-S3-REV-M(1051),
            rcftTypeRC806-30B-FV35-M-REV-M(1052),
            rcftTypeRC806-30B-FV35-S1-REV-M(1053),
            rcftTypeRC806-30B-FV35-S2-REV-M(1054),
            rcftTypeRC806-30B-FV35-S3-REV-M(1055),
            rcftTypeRC802-60B-M-REV-M(1056),
            rcftTypeRC802-60B-S1-REV-M(1057),
            rcftTypeRC802-60B-S2-REV-M(1058),
            rcftTypeRC802-60B-S3-REV-M(1059),
            rcftTypeRC804-60B-M-REV-M(1060),
            rcftTypeRC804-60B-S1-REV-M(1061),
            rcftTypeRC804-60B-S2-REV-M(1062),
            rcftTypeRC804-60B-S3-REV-M(1063),
            rcftTypeRC806-60B-M-REV-M(1064),
            rcftTypeRC806-60B-S1-REV-M(1065),
            rcftTypeRC806-60B-S2-REV-M(1066),
            rcftTypeRC806-60B-S3-REV-M(1067),

            rcftTypeRC906-FXE1-REV-M(1068),
            rcftTypeRC916-FXE1-REV-M(1072),
            rcftTypeRC906-EE1-REV-M(1076),
            rcftTypeRC905-EE1-REV-M(1080),
            rcftTypeRC905-4EE1-REV-M(1084),
            rcftTypeRC902(1088),
     		rcftTypeRC802-30B-FV35-REV-N(1092),
     		rcftTypeRC804-30B-FV35-REV-N(1096),
     		rcftTypeRC806-30B-FV35-REV-N(1100),

            rcftTypeOPCOM200-FEU2-REV-A-SLAVE(10001),
            rcftTypeOPCOM200-FEU1-REV-A-SLAVE(10005),
            rcftTypeRC2002-30FE-REV-A(10008),
            rcftTypeRC602-GE-REV-A-SLAVE(10009),
            rcftTypeRC852-30-REV-A(10010),

            rcftTypeRC521-FE-REV-D(10015),             --作为局端的一个属性
            rcftTypeRC511-4FE-REV-A(10020),
            rcftTypeRC581-FE-REV-A(10029),
            rcftTypeRC601-GEF-REV-A(10035),
            rcftTypeRC521-FE-REV-C(10051),         	  --作为局端的一个属性

            rcftTypeRC581-GE-REV-A(10068),
            rcftTypeRC3101(10073),
            rcftTypeRC531-FE-REV-A(10087),
            rcftTypeRC851-30-FV35-REV-A(10095),
            rcftTypeRCVS1000-501A(10157),
            rcftTypeRC851-30-FV35-REV-B(10178),	--增加V35时隙跟随
            rcftTypeRC1102-FE-REV-A-SLAVE(11000),
            rcftTypeRC852-30-FV35-REV-A(11001),
            rcftTypeRC1102-E1-REV-B-SLAVE(11002),
            rcftTypeRC801-120B-REV-M(11003),
            rcftTypeRC805-120B-REV-M(11004),
            rcftTypeRC552-FE-REV-A-SLAVE(11005),
            rcftTypeRC602-GEF-REV-A-SLAVE(11006),
            rcftTypeOPCOM200-GEU1-SLAVE-REV-A(11007),
            rcftTypeRC852-30-BL-REV-A(11008),
            rcftTypeRC1102-V35-SLAVE-REV-A(11009),
            rcftTypeRC532-2FE-REV-A-SLAVE(11010),
            rcftTypeRC1102-E1-BL-REV-A-SLAVE(11011),
            rcftTypeRC532-FE-REV-A-SLAVE(11012),
            rcftTypeRCVS1000-801A-1DD-REV-A(11015),
            rcftTypeRCVS1000-601A-1DD-REV-A(11016),
            rcftTypeRC802-120L-BL-REV-M(11017),
            rcftTypeRC552-GE-REV-A-SLAVE(11018),
            rcftTypeRC552-FE-REV-A-SLAVE-NEW(11019), --增加了SFP状态的新协议
            rcftTypeRC602-GE-REV-B-SLAVE(11020),
            rcftTypeRC551L-FE-REV-A-SLAVE(11021),
            rcftTypeRC552-GE-REV-B-SLAVE(11025),
            rcftTypeRC852-30-FV35-REV-A1-SLAVE(11027),    --增加了V35带宽跟随
            rcftTypeRC522-FE-REV-D-SLAVE(11029),
            rcftTypeRC522-FE-REV-C-SLAVE(11030),
            rcftTypeRC602E-GE(11033),

            rcftTypeRC521H-FE-DoubleFiber-S(20071),   --双纤台式
            rcftTypeRC521H-FE-SingleFiber-S(20072),   --单纤台式

            rcftUnknownType(999)

        }
        MAX-ACCESS read-only
        STATUS current
        DESCRIPTION
        "
          远端板卡类型.
          An indication of the card type of the remote module.

        "
        ::= { rcftSlotStatEntry 53 }

    rcftRSlotChassisTmpt OBJECT-TYPE
        SYNTAX INTEGER
        MAX-ACCESS read-only
        STATUS current
        DESCRIPTION
          "
          	远端机箱温度,单位为摄氏度.
          "
        ::= { rcftSlotStatEntry 54 }

    rcftSlotExSwitchMode OBJECT-TYPE
        SYNTAX INTEGER
        MAX-ACCESS read-only
        STATUS current
        DESCRIPTION
          "
          	交换控制器的工作方式:(1:直通,2:存储转发).
          "
        ::= { rcftSlotStatEntry 55 }

    rcftSlotRevFluxCount OBJECT-TYPE
      SYNTAX Counter32
      MAX-ACCESS read-only
      STATUS current
      DESCRIPTION
        "
        	本模块流量统计(0-2^24,代表本模块的接收流量统计值).
        "
        ::= {rcftSlotStatEntry 56}

    rcftSlotSedFluxCount OBJECT-TYPE
      SYNTAX Counter32
      MAX-ACCESS read-only
      STATUS current
      DESCRIPTION
        "
        	本模块流量统计(0-2^24,代表本模块的发送流量统计值).
        "
        ::= {rcftSlotStatEntry 57}

    rcftSlotRevFluxTimer OBJECT-TYPE
      SYNTAX Counter32
      MAX-ACCESS read-only
      STATUS current
      DESCRIPTION
        "
        	本模块流量时间统计(0-2^24,代表本模块的接收流量时间统计值).
        "
        ::= {rcftSlotStatEntry 58}

    rcftSlotSedFluxTimer OBJECT-TYPE
      SYNTAX Counter32
      MAX-ACCESS read-only
      STATUS current
      DESCRIPTION
        "
        	本模块流量统计(0-2^24,代表本模块的发送流量时间统计值).
        "
        ::= {rcftSlotStatEntry 59}

    rcftRSlotESpeed OBJECT-TYPE
        SYNTAX INTEGER
        {
            rcft10Mbps(1),
            rcft100Mbps(2),
            rcft1000Mbps(3),
            rcft10Gbps(4),
            other(16)
        }
        MAX-ACCESS read-write
        STATUS current
        DESCRIPTION
         "
       	   远端模块电口的工作速率1:10Mbps,2:100Mbps,3:1000Mbps,4:10Gbps,16:其他).
       	   The speed of the electronic port in the remote module.
            1:10Mbps
            2.100Mbps
            3.1000Mbps
            4.10Gbps
            5.other
         "
        ::= {rcftSlotStatEntry 60}

    rcftRSlotOSpeed OBJECT-TYPE
        SYNTAX INTEGER
        {
            rcft10Mbps(1),
            rcft100Mbps(2),
            rcft1000Mbps(3),
            rcft10Gbps(4),
            other(16)
        }
        MAX-ACCESS read-only
        STATUS current
        DESCRIPTION
          "
          	远端模块光口速率(1:10Mbps,2:100Mbps,3:1000Mbps,4:10Gbps,16:其他).
          "
        ::= {rcftSlotStatEntry 61}

     rcftRSlotORLnk OBJECT-TYPE
    	SYNTAX INTEGER
    	{
    	   linkup(1),
    	   linkdown(2)
    	}
    	MAX-ACCESS read-only
    	STATUS current
    	DESCRIPTION
    	   "
    	  远端模块光口发送方向的link状态(1:linkup,2:linkdown).
    	  The object indicating the status of the optical port
    	  in the receiving direction.
    	  When the value is 1 the optical port link up,otherwise link down.

    	   "
        ::={rcftSlotStatEntry 62}

    rcftRSlotOTLnk OBJECT-TYPE
    	SYNTAX INTEGER
    	{
    	   linkup(1),
    	   linkdown(2)
    	}
    	MAX-ACCESS read-only
    	STATUS current
    	DESCRIPTION
    	   "
    	  远端模块光口发送方向的link状态(1:linkup,2:linkdown).
    	  The object indicating the status of the optical port
    	  in the transmitting direction.
    	  When the value is 1 the optical port links up,otherwise links down.
    	   "
        ::={rcftSlotStatEntry 63}

    rcftSlotE1LOS OBJECT-TYPE
        SYNTAX INTEGER
    	{
    	   normal(1),
    	   disappear(2)
    	}
    	MAX-ACCESS read-only
    	STATUS current
    	DESCRIPTION
        "
   	   	本端模块E1信号状态(1:正常,2:消失).
   	"
        ::={rcftSlotStatEntry 64}

    rcftSlotOLOS OBJECT-TYPE
        SYNTAX INTEGER
    	{
    	   normal(1),
    	   disappear(2)
    	}
    	MAX-ACCESS read-only
    	STATUS current
    	DESCRIPTION
    	   "
    	   	本端模块光信号状态(1:正常,2:消失).
    	   "
        ::={rcftSlotStatEntry 65}

    rcftSlotOSync OBJECT-TYPE
        SYNTAX INTEGER
    	{
    	   normal(1),
    	   loss(2)
    	}
    	MAX-ACCESS read-only
    	STATUS current
    	DESCRIPTION
    	   "
    	   	本端模块光同步信号状态(1:正常,2:丢失).
    	   "
        ::={rcftSlotStatEntry 66}

    rcftSlotOTransErrorCode OBJECT-TYPE
        SYNTAX INTEGER
    	{
    	   less10E-6(1),
    	   more10E-6(2),
    	   more10E-3(3)
    	}
    	MAX-ACCESS read-only
    	STATUS current
    	DESCRIPTION
    	   "
    	  	本端模块光传输误码率(1:小于10E-6,2:大于10E-6,小于10E-3,3:大于10E-3).
    	   "
        ::={rcftSlotStatEntry 67}

    rcftRSlotE1LOS OBJECT-TYPE
        SYNTAX INTEGER
    	{
    	   normal(1),
    	   disappear(2)
    	}
    	MAX-ACCESS read-only
    	STATUS current
    	DESCRIPTION
    	   "
    	   	远端模块E1信号状态(1:正常,2:消失).
    	   "
        ::={rcftSlotStatEntry 68}

    rcftRSlotOLOS OBJECT-TYPE
        SYNTAX INTEGER
    	{
    	   normal(1),
    	   disappear(2)
    	}
    	MAX-ACCESS read-only
    	STATUS current
    	DESCRIPTION
    	   "
    	   	远端模块光信号状态(1:正常,2:消失).
    	   "
        ::={rcftSlotStatEntry 69}

    rcftRSlotOSync OBJECT-TYPE
        SYNTAX INTEGER
    	{
    	   normal(1),
    	   loss(2)
    	}
    	MAX-ACCESS read-only
    	STATUS current
    	DESCRIPTION
    	   "
    	   	远端模块光同步信号状态(1:正常,2:丢失).
    	   "
        ::={rcftSlotStatEntry 70}

    rcftRSlotOTransErrorCode OBJECT-TYPE
        SYNTAX INTEGER
    	{
    	   less10E-6(1),
    	   more10E-6(2),
    	   more10E-3(3)
    	}
    	MAX-ACCESS read-only
    	STATUS current
    	DESCRIPTION
    	   "
    	   	远端模块光传输误码率(1:小于10E-6,2:大于10E-6,小于10E-3,3:大于10E-3).
    	   "
        ::={rcftSlotStatEntry 71}


    rcftSlotE1LOF OBJECT-TYPE
        SYNTAX INTEGER
        {
              normal(1),
    	      loss(2)
        }
        MAX-ACCESS read-only
    	STATUS current
    	DESCRIPTION
    	   "
    	   	E1帧信号状态(1:帧信号正常,2:帧信号失步)
    	   "
        ::={rcftSlotStatEntry 72}

    rcftSlotE1CRC OBJECT-TYPE
        SYNTAX INTEGER
        {
              normal(1),
    	      error(2)
        }
        MAX-ACCESS read-only
    	STATUS current
    	DESCRIPTION
    	   "
    	   	CRC校验状态(1:CRC校验正确,2:CRC校验错误)
    	   "
        ::={rcftSlotStatEntry 73}

    rcftSlotHardWareDescr OBJECT-TYPE
    	SYNTAX  DisplayString
    	MAX-ACCESS  read-only
    	STATUS  current
    	DESCRIPTION
            "
            	A textual description of the siglechip program version.
            "
       ::={rcftSlotStatEntry 74}

   rcftSlotSigleChipDescr OBJECT-TYPE
    	SYNTAX  DisplayString
    	MAX-ACCESS  read-only
    	STATUS  current
    	DESCRIPTION
            "
            	A textual description of the siglechip program version.
            "
       ::={rcftSlotStatEntry 75}


    rcftSlotV35Port OBJECT-TYPE
        SYNTAX INTEGER
        {
              close(1),
    	      open(2)
        }
        MAX-ACCESS read-write
    	STATUS current
    	DESCRIPTION
    	   "
    	   	V35口开关状态,(1:V35处于关闭状态,2:V35处于打开状态.)
    	   "
        ::={rcftSlotStatEntry 76}

    rcftSlotV35RTS OBJECT-TYPE
        SYNTAX INTEGER
        {
              inefficient(1),
    	      efficient(2)
        }
        MAX-ACCESS read-only
    	STATUS current
    	DESCRIPTION
    	   "
    	   	RTS信号状态(1:RTS信号无效,2:RTS信号有效.)
    	   "
        ::={rcftSlotStatEntry 77}

    rcftSlotV35DTR OBJECT-TYPE
        SYNTAX INTEGER
        {
              inefficient(1),
    	      efficient(2)
        }
        MAX-ACCESS read-only
    	STATUS current
    	DESCRIPTION
    	   "
    	   	DTR信号状态(1:RTS信号无效,2:RTS信号有效.)
    	   "
        ::={rcftSlotStatEntry 78}

    rcftSlotE1LoopStatus OBJECT-TYPE
        SYNTAX INTEGER
        {
	   e1port1loop(1),
           e1twoportnormal(2),
           e1port2loop(3),
           e1twoportloop(4)
        }
        MAX-ACCESS read-only
        STATUS current
        DESCRIPTION
          "
         	 模块本地E1环回状态:(1:E1-Port1环回,2:正常(E1-PORT1和E1-PORT2都不环回),
          			  3:E1-PORT2环回,4:E1-PORT1和E1-PORT2都环回).
          "
        ::={rcftSlotStatEntry 79}

    rcftSlotE1LoopSwitchStatus OBJECT-TYPE
        SYNTAX INTEGER
        {
	   e1port1loop(1),
           e1twoportnormal(2),
           e1port2loop(3),
           e1twoportloop(4)
        }
        MAX-ACCESS read-only
        STATUS current
        DESCRIPTION
	"
	  	模块本地E1环回硬件检测开关状态:(1:E1-Port1环回,2:正常(E1-PORT1和E1-PORT2都不环回),
    		      			   3:E1-PORT2环回,4:E1-PORT1和E1-PORT2都环回).
    	"
        ::={rcftSlotStatEntry 80}

    rcftSlotV35LoopStatus OBJECT-TYPE
        SYNTAX INTEGER
        {
	   v35loopok(1),
           v35loopnormal(2)
        }
        MAX-ACCESS read-only
        STATUS current
        DESCRIPTION
          "
          	模块本地V35环回状态:(1:环回,2:正常).
          "
        ::={rcftSlotStatEntry 81}

    rcftSlotV35LoopSwitchStatus OBJECT-TYPE
        SYNTAX INTEGER
        {
	   enable(1),
           disable(2)
        }
        MAX-ACCESS read-only
        STATUS current
        DESCRIPTION
         "
        	模块本地V35环回硬件检测开关:(1:使能,2:禁止).
       "
        ::={rcftSlotStatEntry 82}


    rcftSlotEPort1Link OBJECT-TYPE
        SYNTAX INTEGER
        {
            link(1),
            unlink(2)
        }
        MAX-ACCESS read-only
        STATUS current
        DESCRIPTION
          "
          	本模块电口1LINK(1:LINK, 2:UNLINK).
          "
        ::= {rcftSlotStatEntry 83}

    rcftSlotEPort1AutoNegotiation OBJECT-TYPE
        SYNTAX INTEGER
        {
            auto(1),
            manul(2)
        }
        MAX-ACCESS read-write
        STATUS current
        DESCRIPTION
          "
          	本模块电口1速率协商状态(1:自协商,2:手动).附:对于10M/100M自适应的板卡本属性可用,其余板卡不可用.
          "
        ::= {rcftSlotStatEntry 84}

    rcftSlotEPort1Duplex OBJECT-TYPE
        SYNTAX INTEGER
        {
            full-duplex(1),
            half-duplex(2),
            auto(3)
        }
        MAX-ACCESS read-write
        STATUS current
        DESCRIPTION
          "
          	本模块电口1双工状态(1:全双工,2:半双工,3:自动).
          "
        ::= {rcftSlotStatEntry 85}

    rcftSlotEPort1Speed OBJECT-TYPE
        SYNTAX INTEGER
        {
            rcft10Mbps(1),
            rcft100Mbps(2),
            rcft1000Mbps(3),
            rcft10Gbps(4),
            other(16)
        }
        MAX-ACCESS read-write
        STATUS current
        DESCRIPTION
        "
        	本模块电口1速率(1:10Mbps,2:100Mbps,3:1000Mbps,4:10Gbps,16:其他).
        "
        ::= {rcftSlotStatEntry 86}

   rcftSlotEPort1Port OBJECT-TYPE
       SYNTAX INTEGER
       {
          open(1),
          close(2)
       }
       MAX-ACCESS read-write
       STATUS current
       DESCRIPTION
         "
         	本模块电口1开关状态:(1:打开,2关闭).
         "
       ::={rcftSlotStatEntry 87}

    rcftSlotE2PortBandWidth OBJECT-TYPE
        SYNTAX INTEGER
        {
	    ratioOfOneToOne(1),
            ratioOfTwoToOne(2),
            ratioOfThreeToOne(3),
            ratioOfFourToOne(4),
            ratioOfFiveToOne(5),
            ratioOfTenToOne(10),
            ratioOfOneToTwo(12),
            ratioOfOneToFive(15),
            ratioOfOneToTen(20)
        }
        MAX-ACCESS read-write
        STATUS current
        DESCRIPTION
          "
          	本模块两电口带宽分配比例:(1:1:1,2:2:1,3:3:1,4:4:1 5: 1:5,10: 1:10
          								12: 2:1,15: 1:5,20: 1:10).
          "
        ::= {rcftSlotStatEntry 88}

    rcftSlotV35Speed OBJECT-TYPE
        SYNTAX INTEGER
        MAX-ACCESS read-write
        STATUS current
        DESCRIPTION
          "
          	本模块V35口工作速率:(n * value).
          "
	::= {rcftSlotStatEntry 89}

    rcftSlotV35RateCfg OBJECT-TYPE
        SYNTAX INTEGER
        {
           master(1),
           secondary(2)
        }
        MAX-ACCESS read-write
        STATUS current
        DESCRIPTION
          "
          	本模块V35口速率配置:(1:主控,2:从控).
          "
	::= {rcftSlotStatEntry 90}

    rcftSlotV35RxClk OBJECT-TYPE
        SYNTAX INTEGER
        {
           negative(1),
           positive(2)
        }
        MAX-ACCESS read-write
        STATUS current
        DESCRIPTION
          "
          	本模块V35口RX-CLK相位:(1:反向,2:正向).
          "
	::= {rcftSlotStatEntry 91}

    rcftSlotV35TxClk OBJECT-TYPE
        SYNTAX INTEGER
        {
           negative(1),
           positive(2)
        }
        MAX-ACCESS read-write
        STATUS current
        DESCRIPTION
          "
          	本模块V35口TX-CLK相位:(1:反向,2:正向).
          "
	::= {rcftSlotStatEntry 92}

    rcftSlotV35LoopTest OBJECT-TYPE
        SYNTAX INTEGER
        {
           open(1),
           normal(2)
        }
        MAX-ACCESS read-only
        STATUS current
        DESCRIPTION
          "
          	本模块V35环回测试功能是否执行:(1:执行,2:未执行).
          "
        ::={rcftSlotStatEntry 93}

    rcftSlotRE1LoopTest OBJECT-TYPE
        SYNTAX INTEGER
        {
	   		e1port1loop(1),
           	e1twoportnormal(2),
           	e1port2loop(3),
           	e1twoportloop(4)
        }
        MAX-ACCESS read-only
        STATUS current
        DESCRIPTION
          "
          	本模块远端E1环回测试功能执行情况:1:E1-Port1环回,2:正常(E1-PORT1和E1-PORT2都不环回),
					   3:E1-PORT2环回,4:E1-PORT1和E1-PORT2都环回).
	"
        ::={rcftSlotStatEntry 94}

    rcftSlotRE1LoopStatus OBJECT-TYPE
        SYNTAX INTEGER
        {
	   e1port1loop(1),
           e1twoportnormal(2),
           e1port2loop(3),
           e1twoportloop(4)
        }
        MAX-ACCESS read-only
        STATUS current
        DESCRIPTION
          "
          	本模块远端E1环回状态:(1:E1-Port1环回,2:正常(E1-PORT1和E1-PORT2都不环回),
          			 3:E1-PORT2环回,4:E1-PORT1和E1-PORT2都环回).
          "
        ::={rcftSlotStatEntry 95}

    rcftSlotLoopTestEn OBJECT-TYPE
        SYNTAX INTEGER
        {
	   enable(1),
           disable(2)
        }
        MAX-ACCESS read-only
        STATUS current
        DESCRIPTION
        "
         	网管是否可以对本模块进行环回测试操作:(1:使能,2:禁止).
        "
        ::={rcftSlotStatEntry 96}

    rcftSlotCLKMode OBJECT-TYPE
        SYNTAX INTEGER
        {
	       secondary(1),
	   	   v35terminal(2),
           master(3),
           reserved(4),
           e1PortClk(5),
           gPortClk(6),
           transparent(7)

      }
        MAX-ACCESS read-write
        STATUS current
        DESCRIPTION
          "
          	本模块的工作时钟方式状态:(1:从时钟,2:V35终端时钟,3:主时钟).
			对于通信约定四，两个字节表示：高字节表示时钟源的端口类型，低字节表示端口ID
          "
        ::={rcftSlotStatEntry 97}

    rcftSlotCfgCmdEn OBJECT-TYPE
        SYNTAX INTEGER
        {
	   enable(1),
           disable(2)
        }
        MAX-ACCESS read-only
        STATUS current
        DESCRIPTION
         "
          	网管是否可以对本模块进行配置或命令操作:(1:使能,2:禁止).
         "
        ::={rcftSlotStatEntry 98}

    rcftSlotE1PCM OBJECT-TYPE
        SYNTAX INTEGER
        {
	   pcm31(1),
           pcm30(2)
        }
        MAX-ACCESS read-write
        STATUS current
        DESCRIPTION
          "
          	E1口的成帧方式:(1:PCM31,2:PCM30).
          "
        ::={rcftSlotStatEntry 99}

    rcftSlotE1CRCEn OBJECT-TYPE
        SYNTAX INTEGER
        {
	   	   enable(1),
           disable(2)
        }
        MAX-ACCESS read-write
        STATUS current
        DESCRIPTION
          "
          	E1口的CRC功能特性:(1:使能,2:禁止).
          "
        ::={rcftSlotStatEntry 100}

    rcftSlotE1AIS OBJECT-TYPE
        SYNTAX INTEGER
        {
              normal(1),
    	      loss(2)
        }
        MAX-ACCESS read-only
        STATUS current
        DESCRIPTION
          "
          	E1口的AIS的状态:(1:正常,2:告警).
          "
        ::={rcftSlotStatEntry 101}

    rcftSlotRALM OBJECT-TYPE
        SYNTAX INTEGER
        {
              normal(1),
    	      loss(2)
        }
        MAX-ACCESS read-only
        STATUS current
        DESCRIPTION
          "
          	远端模块总告警的状态:(1:正常,2:告警).
          "
        ::={rcftSlotStatEntry 102}


    rcftSlotE1Transparent OBJECT-TYPE
        SYNTAX INTEGER
        {
              transparent(1),
    	      pcm(2)
        }
        MAX-ACCESS read-write
        STATUS current
        DESCRIPTION
          "
          	模块E1口工作模式:(1:透明方式,2:成帧方式).
          "
        ::={rcftSlotStatEntry 103}

    rcftSlotEthTransmitSpeed OBJECT-TYPE
        SYNTAX INTEGER
        MAX-ACCESS read-write
        STATUS current
        DESCRIPTION
          "
          	本模块以太网口转发速率:(n * value).
          "
	::= {rcftSlotStatEntry 104}

    rcftSlotE1Port2LOS OBJECT-TYPE
        SYNTAX INTEGER
    	{
    	   normal(1),
    	   disappear(2)
    	}
    	MAX-ACCESS read-only
    	STATUS current
    	DESCRIPTION
  	   "
  	   	本端模块E12支路信号状态(1:正常,2:消失).
  	   "
        ::={rcftSlotStatEntry 105}

    rcftRSlotE1Port2LOS OBJECT-TYPE
        SYNTAX INTEGER
    	{
    	   normal(1),
    	   disappear(2)
    	}
    	MAX-ACCESS read-only
    	STATUS current
    	DESCRIPTION
       "
       	远端模块E12支路信号状态(1:正常,2:消失).
       "
        ::={rcftSlotStatEntry 106}


    rcftSlotRE1LoopSwitchStatus OBJECT-TYPE
        SYNTAX INTEGER
        {
	   e1port1loop(1),
           e1twoportnormal(2),
           e1port2loop(3),
           e1twoportloop(4)
        }
        MAX-ACCESS read-only
        STATUS current
        DESCRIPTION
          "
          	本模块远端E1环回硬件检测开关:(1:E1-Port1环回,2:正常(E1-PORT1和E1-PORT2都不环回),
    		      			 3:E1-PORT2环回,4:E1-PORT1和E1-PORT2都环回).
    		"
        ::={rcftSlotStatEntry 107}

    rcftSlotFrameLength OBJECT-TYPE
        SYNTAX INTEGER
        {
           framelen1916B(1),
    	   framelen1536B(2),
           framelen9728B(3),
    	   framelen1518B(4),
    	   framelen9kB(5),
    	   framelen2048(6)

        }
        MAX-ACCESS read-write
        STATUS current
        DESCRIPTION
          "
          	本模块以太网帧的最大帧长:(1:1916B,2:1536B).
          	The max frame length of the ethernet port in the local module.
          "
        ::={rcftSlotStatEntry 108}

    rcftSlotRecvRestrictSpeed OBJECT-TYPE
        SYNTAX INTEGER
        MAX-ACCESS read-write
        STATUS current
        DESCRIPTION
          "
          本模块接收限定速率:(n * value;n = 0,1,2....3200.... value = 32kb/s).
          该速率是接收方向给业务分配的实际带宽.
          针对112-GE(REV.A)板卡,value: 80 kb/s(10M),800 kb/s(100M),8000 kb/s(1000M)
          The value of this object is the actual receiving bandwidth that the local module supplies
          for the operation.
          "
	::= {rcftSlotStatEntry 109}

    rcftSlotSendRestrictSpeed OBJECT-TYPE
        SYNTAX INTEGER
        MAX-ACCESS read-write
        STATUS current
        DESCRIPTION
          "
          本模块发送限定速率:(n * value;n = 0,1,2....3200.... value = 32kb/s).
          该速率是发送方向给业务分配的实际带宽.带宽最大值是100M.
          The value of this object is the actual transmitting bandwidth that the local module supplies
          for the operation.
          "
	::= {rcftSlotStatEntry 110}

    rcftRSlotFrameLength OBJECT-TYPE
        SYNTAX INTEGER
        {
           framelen1916B(1),
    	   framelen1536B(2),
           framelen9728B(3),
    	   framelen1518B(4),
    	   framelen9kB(5),
    	   framelen2048B(6)
        }
        MAX-ACCESS read-write
        STATUS current
        DESCRIPTION
          "
          远端模块以太网帧的最大帧长:(1:1916B,2:1536B).
          The max frame length of the ethernet port in the remote module.
          1:1916B
          2:1536B
          "
        ::={rcftSlotStatEntry 111}

    rcftRSlotVLAN OBJECT-TYPE
        SYNTAX INTEGER
        {
              port-vlan(1),
    	      not-support(2),
    	      tag-vlan(3)
        }
        MAX-ACCESS read-write
        STATUS current
        DESCRIPTION
          "
          	远端模块工作方式:(1:PORT-VLAN,2:不支持VLAN,3:TAG-VLAN).
          "
        ::={rcftSlotStatEntry 112}

    rcftSlotLALM OBJECT-TYPE
        SYNTAX INTEGER
        {
              normal(1),
    	      loss(2)
        }
    	MAX-ACCESS read-only
        STATUS current
        DESCRIPTION
          "
          	局端端模块总告警的状态:(1:正常,2:告警).
          "
        ::={rcftSlotStatEntry 113}

    rcftSlotChipOpMode OBJECT-TYPE
	SYNTAX INTEGER
        {
              old(1),
    	      new(2)
        }
    	MAX-ACCESS read-only
        STATUS current
        DESCRIPTION
          "
          	远端设备的芯片版本:(1:旧版,2:新版).
          "
        ::={rcftSlotStatEntry 114}

      rcftSlotAutoCutErrLineEn OBJECT-TYPE
        SYNTAX INTEGER
        {
              enable(1),
    	      disable(2)
        }
    	MAX-ACCESS read-write
        STATUS current
        DESCRIPTION
          "
         	本端设备误码自动切断功能:(1:使能,2:禁止).
          "
        ::={rcftSlotStatEntry 115}


    rcftSlotRamBD OBJECT-TYPE
        SYNTAX INTEGER
        {
              less256Kbps(1),
    	      more256Kbps(2),
    	      more512Kbps(3),
	      more1Mbps(4),
	      more2Mbps(5)

        }
        MAX-ACCESS read-write
        STATUS current
        DESCRIPTION
          "
          	模块缓存区优化3位编码:(1:小于256kbps,2:大于256Kbps,3:大于512Kbps,4:大于1Mbps,5:大于2Mbps,).
          "
        ::={rcftSlotStatEntry 116}

    rcftSlotV35DSR OBJECT-TYPE
        SYNTAX INTEGER
        {
              signal(1),
    	      nosignal(2)
        }
        MAX-ACCESS read-only
        STATUS current
        DESCRIPTION
          "
          	V35端口的DSR信后输入:(1:有DSR信号,2:无DSR信号).
          "
        ::={rcftSlotStatEntry 117}

    rcftSlotV35DCD OBJECT-TYPE
        SYNTAX INTEGER
        {
              signal(1),
    	      nosignal(2)
        }
        MAX-ACCESS read-only
        STATUS current
        DESCRIPTION
          "
          	V35端口的DCD信后输入:(1:有DCD信号,2:无DCD信号).
          "
        ::={rcftSlotStatEntry 118}

    rcftRSlotRecvRestrictSpeed OBJECT-TYPE
      SYNTAX INTEGER
        MAX-ACCESS read-write
        STATUS current
        DESCRIPTION
          "
         远端模块接收限定速率:(n * value;n = 0,1,2....3200. value = 32kb/s).
         该速率是接收方向给业务分配的实际带宽.带宽最大值是100M.
         The value of this object is the actual receiving bandwidth that the remote module supplies
         for the operation.
          "
	::= {rcftSlotStatEntry 119}

    rcftRSlotSendRestrictSpeed OBJECT-TYPE
      SYNTAX INTEGER
      MAX-ACCESS read-write
        STATUS current
        DESCRIPTION
          "
          远端模块发送限定速率:(n * value;n = 0,1,2....3200. value = 32kb/s).
          该速率是发送方向给业务分配的实际带宽. 带宽最大值是100M.
          The value of this object is the actual transmitting bandwidth that the remote module supplies
          for the operation.

          "
	::= {rcftSlotStatEntry 120}

    rcftRSlotV35Speed OBJECT-TYPE
        SYNTAX INTEGER
        MAX-ACCESS read-write
        STATUS current
        DESCRIPTION
          "
          	远端模块V35口工作速率:(n * value).
          "
	::= {rcftSlotStatEntry 121}

    rcftRSlotCLKMode OBJECT-TYPE
        SYNTAX INTEGER
        {
	   		secondary(1),
	   		v35terminal(2),
           	master(3),
           	reserved(4)

        }
        MAX-ACCESS read-write
        STATUS current
        DESCRIPTION
          "
          	远端模块的工作时钟方式状态:(1:从时钟,2:V35终端时钟,3:主时钟).
          "
        ::={rcftSlotStatEntry 122}

    rcftSlotWorkStatus OBJECT-TYPE
      SYNTAX INTEGER
        MAX-ACCESS read-write
        STATUS current
        DESCRIPTION
          "
          	模块的本端与远端的工作状态.
       注:在对该对象进行配置操作时,在绑定该对象的同时,需要绑定针对某一槽位的板卡类型
       rcftSlotConfCardType,如果是对本端模块进行配置操作,需要本端的板卡类型赋给rcftSlotConfCardType;
       如果是对远端模块进行配置操作,需要将远端的板卡类型赋给rcftSlotConfCardType.

          "
	::= {rcftSlotStatEntry 123}

    rcftTxWorkStatus OBJECT-TYPE
      SYNTAX INTEGER
        MAX-ACCESS read-write
        STATUS current
        DESCRIPTION
          "
          	模块的本端与远端以太网口的工作状态.

       注:在对该对象进行配置操作时,在绑定该对象的同时,需要绑定针对某一槽位的板卡类型
       rcftSlotConfCardType,如果是对本端模块进行配置操作,需要本端的板卡类型赋给rcftSlotConfCardType;
       如果是对远端模块进行配置操作,需要将远端的板卡类型赋给rcftSlotConfCardType.

          "
	::= {rcftSlotStatEntry 124}

    rcftFxWorkStatus OBJECT-TYPE
      SYNTAX INTEGER
        MAX-ACCESS read-write
        STATUS current
        DESCRIPTION
          "
          	模块的本端与远端光口的工作状态.
          "
	::= {rcftSlotStatEntry 125}


    rcftE1WorkStatus OBJECT-TYPE
      SYNTAX INTEGER
        MAX-ACCESS read-write
        STATUS current
        DESCRIPTION
          "
              模块的本端与远端E1端口的工作状态.

              注:在对该对象进行配置操作时,在绑定该对象的同时,需要绑定针对某一槽位的板卡类型
              rcftSlotConfCardType,如果是对本端模块进行配置操作,需要本端的板卡类型赋给rcftSlotConfCardType;
              如果是对远端模块进行配置操作,需要将远端的板卡类型赋给rcftSlotConfCardType.

          "
	::= {rcftSlotStatEntry 126}

    rcftV35WorkStatus OBJECT-TYPE
      SYNTAX INTEGER
        MAX-ACCESS read-write
        STATUS current
        DESCRIPTION
          "
          	模块的本端与远端V35口信息.
                注:在对该对象进行配置操作时,在绑定该对象的同时,需要绑定针对某一槽位的板卡类型
                rcftSlotConfCardType,如果是对本端模块进行配置操作,需要本端的板卡类型赋给rcftSlotConfCardType;
                如果是对远端模块进行配置操作,需要将远端的板卡类型赋给rcftSlotConfCardType.

          "
	::= {rcftSlotStatEntry 127}

    rcftAllLoopSwitch OBJECT-TYPE
      SYNTAX INTEGER
        MAX-ACCESS read-only
        STATUS current
        DESCRIPTION
          "
          	用户端和线路端环回开关状态
          "
	::= {rcftSlotStatEntry 128}

    rcftSlotE1PortAlarm OBJECT-TYPE
      SYNTAX INTEGER
        MAX-ACCESS read-only
        STATUS current
        DESCRIPTION
          "
          	本端模块E1端口的告警信息.
          "
	::= {rcftSlotStatEntry 129}

    rcftRSlotE1PortAlarm OBJECT-TYPE
      SYNTAX INTEGER
        MAX-ACCESS read-write
        STATUS current
        DESCRIPTION
          "
          	远端模块E1端口的告警信息及告警屏蔽.
          "
	::= {rcftSlotStatEntry 130}

    rcftRSlotHardWareDescr OBJECT-TYPE
    	SYNTAX  DisplayString
    	MAX-ACCESS  read-only
    	STATUS  current
    	DESCRIPTION
            "
            	A textual description of the siglechip program version.
            "
       ::={rcftSlotStatEntry 131}

   rcftRSlotSigleChipDescr OBJECT-TYPE
    	SYNTAX  DisplayString
    	MAX-ACCESS  read-only
    	STATUS  current
    	DESCRIPTION
            "
            	A textual description of the siglechip program version.
            "
       ::={rcftSlotStatEntry 132}

    rcftSlotConfCardType OBJECT-TYPE
      SYNTAX INTEGER
        MAX-ACCESS read-write
        STATUS current
        DESCRIPTION
          "
          	所配置模块的类型.
          	特别说明：在对rcftSlotWorkStatus.rcftTxWorkStatus等既表示局端又表示远端的位定义对象
          	进行配置操作时需要绑定该对象,当对局端板卡进行配置时该对象绑定局端的板卡类型,
          	当对远端板卡配置时需要绑定远端的板卡类型.
          "
	::= {rcftSlotStatEntry 133}

     rcftSlotLineStatus OBJECT-TYPE
        SYNTAX INTEGER
        {
	   remoteNoPower(1),
	   remotePowerNormal(2)
        }
        MAX-ACCESS read-only
        STATUS current
        DESCRIPTION
          "
          	link down时局端与远端的链路掉电状态:(1:远端模块掉电,2:正常)
          "
	::= {rcftSlotStatEntry 134}

    rcftV35E1PortExtendStatus OBJECT-TYPE
      SYNTAX INTEGER
        MAX-ACCESS read-write
        STATUS current
        DESCRIPTION
          "
          	模块的本端与远端V35口,E1口扩展信息.

                注:在对该对象进行配置操作时,在绑定该对象的同时,需要绑定针对某一槽位的板卡类型
                rcftSlotConfCardType,如果是对本端模块进行配置操作,需要本端的板卡类型赋给rcftSlotConfCardType;
                如果是对远端模块进行配置操作,需要将远端的板卡类型赋给rcftSlotConfCardType.

          "
	::= {rcftSlotStatEntry 135}

    rcftSlotDoubleLoopSwitch OBJECT-TYPE
        SYNTAX INTEGER
        {
	   localDoubleLoop(1),
	   remoteDoubleLoop(2),
	   normal(3),
	   port2localDoubleLoop(4),
	   port2remoteDoubleLoop(5),
	   port1localDoubleLoop(6),
	   port1remoteDoubleLoop(7)

        }
        MAX-ACCESS read-only
        STATUS current
        DESCRIPTION
          "
          	本端设备的双向环回开关状态:
          	(1:对端双向环回,2:本段双向环回,3:正常,4:第2路E1本端双向环回,5:第2路E1远端双向环回,6:第1路E1本端双向环回,7:第1路E1远端双向环回)
          "
	::= {rcftSlotStatEntry 136}

    rcftRSlotDoubleLoopSwitch OBJECT-TYPE
        SYNTAX INTEGER
        {
	   localDoubleLoop(1),
	   remoteDoubleLoop(2),
	   normal(3),
	   port2localDoubleLoop(4),
	   port2remoteDoubleLoop(5),
	   port1localDoubleLoop(6),
	   port1remoteDoubleLoop(7)
        }
        MAX-ACCESS read-only
        STATUS current
        DESCRIPTION
          "
          	对端设备的双向环回开关状态:(1:对端双向环回,2:本段双向环回,3:正常)
          "
	::= {rcftSlotStatEntry 137}


    rcftRSlotOport OBJECT-TYPE
       SYNTAX INTEGER
       {
          open(1),
          close(2)
       }
       MAX-ACCESS read-write
       STATUS current
       DESCRIPTION
         "
         远端模块光口开关使能:(1:打开,2关闭).
         Open or close the optical port in the remote module.
         "
       ::={rcftSlotStatEntry 138}

     ---以下是对CWDM MIB 的定义

     --**********************************--
     -- 这一部分是模块盘的配置和状态信息
     --**********************************--

      cwdmClientWorkSpeed OBJECT-TYPE
      	SYNTAX INTEGER
      	{
      	    stm16-C48(1),
      	    ge-Gb(2),
      	    stm4-C12(3),
      	    stm1-C3(4),
      	    fe(5),
      	    auto(6),
      	    reserved(7),
      	    speed2fc(8),
			speedfc(9),
			bypass (10),
			stm16-fec(11)
      	}
      	MAX-ACCESS read-write
      	STATUS current
      	DESCRIPTION
      	"
      	    模块盘速率
      	"
      	::={rcftSlotStatEntry 139}


    --********************************--
    -- cwdm侧接口配置和工作状态信息
    --********************************--

       cwdmCWDMWorkStatus OBJECT-TYPE
       	SYNTAX INTEGER
        MAX-ACCESS read-write
        STATUS current
        DESCRIPTION
        "
          	模块的本端与远端CWDM侧的状态信息.

                注:在对该对象进行配置操作时,在绑定该对象的同时,需要绑定针对某一槽位的板卡类型
                rcftSlotConfCardType,如果是对本端模块进行配置操作,需要本端的板卡类型赋给rcftSlotConfCardType;
                如果是对远端模块进行配置操作,需要将远端的板卡类型赋给rcftSlotConfCardType.
        "
        ::={rcftSlotStatEntry 140}


       cwdmCWDMModuleMaxSpeed OBJECT-TYPE
       	 SYNTAX INTEGER
       	 MAX-ACCESS read-only
       	 STATUS current
       	 DESCRIPTION
       	 "
       	   cwdm侧接口模块的最大速率
         "
       	 ::={rcftSlotStatEntry 141}

       cwdmCWDMModuleTransLen OBJECT-TYPE
       	SYNTAX INTEGER
       	MAX-ACCESS read-only
       	STATUS current
       	DESCRIPTION
       	"
       	 cwdm侧SFP模块在单模光纤中的传输距离(单位为Km)
       	"
       	::={rcftSlotStatEntry 142}

       cwdmCWDMModuleWaveLen OBJECT-TYPE
       	SYNTAX INTEGER
       	MAX-ACCESS read-only
       	STATUS current
       	DESCRIPTION
       	"
       	  cwdm侧SFP模块工作波长(单位为nm)
       	"
       	::={rcftSlotStatEntry 143}

       cwdmCWDMModuleManufacturer  OBJECT-TYPE
       	SYNTAX OCTET STRING(SIZE (0..30))
       	MAX-ACCESS read-only
       	STATUS current
       	DESCRIPTION
       	"
       	 cwdm侧SFP模块的制造商
       	"
       	::={rcftSlotStatEntry 144}

       cwdmCWDMModuleDescr OBJECT-TYPE
        SYNTAX OCTET STRING(SIZE (0..30))
        MAX-ACCESS read-only
        STATUS current
        DESCRIPTION
        "
          cwdm侧产品型号
        "
        ::={rcftSlotStatEntry 145}

       cwdmCWDMModuleVersion OBJECT-TYPE
        SYNTAX OCTET STRING(SIZE (0..10))
        MAX-ACCESS read-only
        STATUS current
        DESCRIPTION
        "
          cwdm侧SFP模块的版本号
        "
        ::={rcftSlotStatEntry 146}

       cwdmCWDMModuleSerialNumber OBJECT-TYPE
        SYNTAX OCTET STRING(SIZE (0..30))
        MAX-ACCESS read-only
        STATUS current
        DESCRIPTION
        "
          cwdm侧SFP模块的序列号
        "
        ::={rcftSlotStatEntry 147}


    --********************************--
    -- cwdm client侧接口配置和工作状态信息
    --********************************--

       cwdmClientWorkStatus OBJECT-TYPE
       	SYNTAX INTEGER
        MAX-ACCESS read-write
        STATUS current
        DESCRIPTION
        "
          	模块的本端与远端CLIENT侧的状态信息.

                注:在对该对象进行配置操作时,在绑定该对象的同时,需要绑定针对某一槽位的板卡类型
                rcftSlotConfCardType,如果是对本端模块进行配置操作,需要本端的板卡类型赋给rcftSlotConfCardType;
                如果是对远端模块进行配置操作,需要将远端的板卡类型赋给rcftSlotConfCardType.
        "
        ::={rcftSlotStatEntry 148}

       cwdmClientModuleMaxSpeed OBJECT-TYPE
       	 SYNTAX INTEGER
       	 MAX-ACCESS read-only
       	 STATUS current
       	 DESCRIPTION
       	 "
       	   client侧接口模块的最大速率
       	 "
       	 ::={rcftSlotStatEntry 149}

       cwdmClientModuleInterfaceType OBJECT-TYPE
       	 SYNTAX INTEGER
       	 MAX-ACCESS read-only
       	 STATUS current
       	 DESCRIPTION
		 "
		   client侧传输媒质(单模/多模)
		 "
       	 ::={rcftSlotStatEntry 150}

       cwdmClientModuleTransLen OBJECT-TYPE
       	SYNTAX INTEGER
       	MAX-ACCESS read-only
       	STATUS current
       	DESCRIPTION
       	"
       	 client侧SFP模块在单模/多模光纤中的传输距离
       	"
       	::={rcftSlotStatEntry 151}

       cwdmClientModuleWaveLen OBJECT-TYPE
       	SYNTAX INTEGER
       	MAX-ACCESS read-only
       	STATUS current
       	DESCRIPTION
       	"
       	  client侧SFP模块工作波长
       	"
       	::={rcftSlotStatEntry 152}

       cwdmClientModuleManufacturer  OBJECT-TYPE
       	SYNTAX OCTET STRING(SIZE (0..30))
       	MAX-ACCESS read-only
       	STATUS current
       	DESCRIPTION
       	"
       	 client侧SFP模块的制造商
       	"
       	::={rcftSlotStatEntry 153}

       cwdmClientModuleDescr OBJECT-TYPE
        SYNTAX OCTET STRING(SIZE (0..30))
        MAX-ACCESS read-only
        STATUS current
        DESCRIPTION
        "
          client侧模块产品型号
        "
        ::={rcftSlotStatEntry 154}

       cwdmClientModuleVersion OBJECT-TYPE
        SYNTAX OCTET STRING(SIZE (0..10))
        MAX-ACCESS read-only
        STATUS current
        DESCRIPTION
        "
          client侧SFP模块的版本号
        "
        ::={rcftSlotStatEntry 155}

       cwdmClientModuleSerialNumber OBJECT-TYPE
        SYNTAX OCTET STRING(SIZE (0..30))
        MAX-ACCESS read-only
        STATUS current
        DESCRIPTION
        "
          client侧SFP模块的流水号
        "
        ::={rcftSlotStatEntry 156}


       cwdmCWDMWorkSpeed OBJECT-TYPE
      	SYNTAX INTEGER
      	{
      	    stm16-C48(1),
      	    ge-Gb(2),
      	    stm4-C12(3),
      	    stm1-C3(4),
      	    fe(5),
      	    auto(6),
      	    reserved(7)
      	}
      	MAX-ACCESS read-write
      	STATUS current
      	DESCRIPTION
      	"
      	   CWDM侧CDR的工作速率
      	"
      	::={rcftSlotStatEntry 157}

      	opticalModuleType OBJECT-TYPE
      	  SYNTAX INTEGER
      	  {
      	     optical-M(1),
      	     optical-S1(2),
      	     optical-S2(3),
      	     optical-S3(4),
      	     optical-SS13(5),
      	     optical-SS15(6),
      	     optical-SS23(7),
      	     optical-SS25(8),
      	     --optical-SS3(9),   kuanglili 20090519 根据公司规范取消ss3光头类型
      	     optical-SS34(9),
      	     optical-SS35(10),
      	     optical-S15(12),  --kuanglili 20090826 s15光模块类型枚举值为12
      	     optical-SFP(15),  --wangjunduo 20130508 SFP光模块类型枚举值为15
      	     optical-S1FC(50),
      	     optical-S1A(51),
      	     optical-S2A(52),
      	     optical-S3A(53),
      	     unknown-type(100)
      	  }
      	  MAX-ACCESS read-only
      	  STATUS current
      	  DESCRIPTION
      	  "
      	     局端模块的光模块类型
      	  "
      	  ::={rcftSlotStatEntry 158}

       rcftSlotInformation OBJECT-TYPE
            SYNTAX OCTET STRING(SIZE (0..100))
          	MAX-ACCESS read-only
          	STATUS current
          	DESCRIPTION
          	"
          	    局端板卡的版本信息:版本信息的格式是:A.x-X.x-Ex-Fx.y
                其中:A.x为硬件版本号;X.x为软件版本号;Ex中的x为以太网交换芯片类型;
                Fx.y中的x为FPGA芯片代号,y为FPGA代码版本号.
          	"
          	::={rcftSlotStatEntry 159}


       	remoteOpticalModuleType OBJECT-TYPE
       	SYNTAX INTEGER
      	  {
      	     optical-M(1),
      	     optical-S1(2),
      	     optical-S2(3),
      	     optical-S3(4),
      	     optical-SS13(5),
      	     optical-SS15(6),
      	     optical-SS23(7),
      	     optical-SS25(8),
      	     --optical-SS3(9),  kuanglili 20090519 根据公司规范取消ss3光头类型
      	     optical-SS34(9),
      	     optical-SS35(10),
      	     optical-S15(12),   --kuanglili 20090826 S15枚举值为12
      	     optical-SFP(15),   --wangjunduo 20130508 SFP光模块类型枚举值为15
      	     optical-S1FC(50),
      	     optical-S1A(51),
      	     optical-S2A(52),
      	     optical-S3A(53),
      	     unknown-type(100)
      	  }
      	  MAX-ACCESS read-only
      	  STATUS current
      	  DESCRIPTION
      	  "
      	    远端板卡的光模块类型
      	  "
      	  ::={rcftSlotStatEntry 160}

       rcftRSlotInformation OBJECT-TYPE
          	SYNTAX OCTET STRING(SIZE (0..100))
          	MAX-ACCESS read-only
          	STATUS current
          	DESCRIPTION
          	"
          	    远端板卡的版本信息版本信息的格式是:A.x-X.x-Ex-Fx.y
                其中:A.x为硬件版本号;X.x为软件版本号;Ex中的x为以太网交换芯片类型;
                Fx.y中的x为FPGA芯片代号,y为FPGA代码版本号.
          	"
          	::={rcftSlotStatEntry 161}


        rcftRSlotRevFluxCount OBJECT-TYPE
        	SYNTAX INTEGER
        	MAX-ACCESS read-only
        	STATUS current
        	DESCRIPTION
        	"
        		远端板卡两次查询间的接收流量差
        	"
        	::={rcftSlotStatEntry 162}

        rcftRSlotSedFluxCount OBJECT-TYPE
        	SYNTAX INTEGER
        	MAX-ACCESS read-only
        	STATUS current
        	DESCRIPTION
        	"
        		远端板卡两次查询间的接收流量差
        	"
        	::={rcftSlotStatEntry 163}

        rcftRSlotRevFluxTimer OBJECT-TYPE
        	SYNTAX INTEGER
        	MAX-ACCESS read-only
        	STATUS current
        	DESCRIPTION
        	"
        	    远端板卡两次接收流量查询间的统计时间
        	"
        	::={rcftSlotStatEntry 164}


        rcftRSlotSedFluxTimer OBJECT-TYPE
        	SYNTAX INTEGER
        	MAX-ACCESS read-only
        	STATUS current
        	DESCRIPTION
        	"
        	    远端板卡两次发送流量查询间的统计时间
        	"
            ::={rcftSlotStatEntry 165}

		rcftSlotRevErrFluxCnt OBJECT-TYPE
			SYNTAX INTEGER
			MAX-ACCESS read-only
			STATUS current
			DESCRIPTION
			"
				局端板卡两次查询间接收到的错误帧
			"
			::={rcftSlotStatEntry 166}

		 rcftSlotSedErrFluxCnt OBJECT-TYPE
		 	SYNTAX INTEGER
		 	MAX-ACCESS read-only
		 	STATUS current
		 	DESCRIPTION
		 	"
		 		局端板卡两次查询间发送到的错误帧
		 	"
		 	::={rcftSlotStatEntry 167}

		  cwdmOMUmoduleType OBJECT-TYPE
       		SYNTAX INTEGER
       		{
       		   wave-seperate(1),
       		   wave-unite(2),
       		   wave-coupling-4(3),
       		   reserved(4)
       		}
       		MAX-ACCESS read-only
       		STATUS current
       		DESCRIPTION
       		"
       		   OPCOM200-OMU4E设备的光路模块类型.
       		   1:分波器,2:合波器,3:4路耦合器,4:reserved
       		"
       		::={rcftSlotStatEntry 168}

       	rcftSlotE1TimeSlot OBJECT-TYPE
       		SYNTAX Unsigned32
       		MAX-ACCESS read-write
       		STATUS current
       		DESCRIPTION
       		"
       		   局端E1时隙
       		   0-30位分别表示E1的31个时隙,置1表示该时隙使能,0表示该时隙禁止
       		"
       	    ::={rcftSlotStatEntry 169}

       	rcftSlotWANRevFluxPacket OBJECT-TYPE
       		SYNTAX INTEGER
       		MAX-ACCESS read-only
       		STATUS current
       		DESCRIPTION
       		"
       		   线路侧接收以太网包统计数
       		"
       		::={rcftSlotStatEntry 170}

       	rcftSlotWANRevFluxCount  OBJECT-TYPE
       		SYNTAX INTEGER
       		MAX-ACCESS read-only
       		STATUS current
       		DESCRIPTION
       		"
       		  线路侧接收以太网字节数
       		"
       	    ::={rcftSlotStatEntry 171}

       	rcftSlotWANSedFluxPacket OBJECT-TYPE
            SYNTAX INTEGER
       		MAX-ACCESS read-only
       		STATUS current
       		DESCRIPTION
       		"
       		   线路侧发送以太网包统计数
       		"
       		::={rcftSlotStatEntry 172}

        rcftSlotWANSedFluxCount OBJECT-TYPE
       		SYNTAX INTEGER
       		MAX-ACCESS read-only
       		STATUS current
       		DESCRIPTION
       		"
       		  线路侧发送以太网字节数
       		"
       	    ::={rcftSlotStatEntry 173}

        rcftSlotWANRevErrFluxPacket  OBJECT-TYPE
       		SYNTAX INTEGER
       		MAX-ACCESS read-only
       		STATUS current
       		DESCRIPTION
       		"
       		  线路侧接收错误以太网包字节数
       		"
       	    ::={rcftSlotStatEntry 174}

        rcftSlotRevFluxPacket  OBJECT-TYPE
       		SYNTAX INTEGER
       		MAX-ACCESS read-only
       		STATUS current
       		DESCRIPTION
       		"
       		   客户侧接收以太网包统计数
       		"
       		::={rcftSlotStatEntry 175}

        rcftSlotSedFluxPacket OBJECT-TYPE
       		SYNTAX INTEGER
       		MAX-ACCESS read-only
       		STATUS current
       		DESCRIPTION
       		"
       		   客户侧发送以太网包统计数
       		"
       		::={rcftSlotStatEntry 176}

        rcftRSlotE1TimeSlot  OBJECT-TYPE
       		SYNTAX Unsigned32
       		MAX-ACCESS read-write
       		STATUS current
       		DESCRIPTION
       		"
       		   远端E1时隙
       		   0-30位分别表示E1的31个时隙,置1表示该时隙使能,0表示该时隙禁止
       		"
       	    ::={rcftSlotStatEntry 177}

            rcftRSlotWANRevFluxPacket  OBJECT-TYPE
       		SYNTAX INTEGER
       		MAX-ACCESS read-only
       		STATUS current
       		DESCRIPTION
       		"
       		   远端模块线路侧接收以太网包统计数
       		"
       		::={rcftSlotStatEntry 178}

            rcftRSlotWANRevFluxCount OBJECT-TYPE
       		SYNTAX INTEGER
       		MAX-ACCESS read-only
       		STATUS current
       		DESCRIPTION
       		"
       		  远端模块线路侧接收以太网包字节数
       		"
       	    ::={rcftSlotStatEntry 179}

            rcftRSlotWANSedFluxPacket OBJECT-TYPE
            SYNTAX INTEGER
       		MAX-ACCESS read-only
       		STATUS current
       		DESCRIPTION
       		"
       		   远端模块线路侧发送以太网包统计数
       		"
       		::={rcftSlotStatEntry 180}

            rcftRSlotWANSedFluxCount OBJECT-TYPE
       		SYNTAX INTEGER
       		MAX-ACCESS read-only
       		STATUS current
       		DESCRIPTION
       		"
       		  远端模块线路侧发送以太网包字节数
       		"
       	    ::={rcftSlotStatEntry 181}

            rcftRSlotWANRevErrFluxPacket OBJECT-TYPE
     		SYNTAX INTEGER
       		MAX-ACCESS read-only
       		STATUS current
       		DESCRIPTION
       		"
       		  远端模块线路侧接收错误以太网包字节数
       		"
       	    ::={rcftSlotStatEntry 182}

            rcftRSlotRevFluxPacket OBJECT-TYPE
     		SYNTAX INTEGER
       		MAX-ACCESS read-only
       		STATUS current
       		DESCRIPTION
       		"
       		   远端模块客户侧接收以太网包统计数
       		"
       		::={rcftSlotStatEntry 183}

            rcftRSlotSedFluxPacket OBJECT-TYPE
    		SYNTAX INTEGER
       		MAX-ACCESS read-only
       		STATUS current
       		DESCRIPTION
       		"
       		   远端模块客户侧发送以太网包统计数
       		"
       		::={rcftSlotStatEntry 184}

      rcftRSlotRevErrFluxCnt  OBJECT-TYPE
       		SYNTAX INTEGER
       		MAX-ACCESS read-only
       		STATUS current
       		DESCRIPTION
       		"
       		  远端模块客户侧接收错误以太网包统计数
       		"
       	    ::={rcftSlotStatEntry 185}

       rcftExtentWorkStatus OBJECT-TYPE
       	    SYNTAX INTEGER
       	    MAX-ACCESS read-write
       	    STATUS current
       	    DESCRIPTION
       	    "
       	    	扩展的状态字节
		   		--------------------------------------------------------------
		       	| Bit15 | Bit14 | Bit13 | Bit12 | Bit11 | Bit10 |Bit9 | Bit8 |
		       	--------------------------------------------------------------
		        ---------------------------------------------------------
		        | Bit7 | Bit6 | Bit5 | Bit4 | Bit3 | Bit2 | Bit1 | Bit0 |
		        ---------------------------------------------------------

		        其他位保留
				Bit8:远端设备的工作模式:1:主控,0:从控
     	    	Bit0:本端设备的工作模式,1:主控,0:从控

       	    "
       	    ::={rcftSlotStatEntry 186}

    rcftSlotE1ESCnt OBJECT-TYPE
    	SYNTAX INTEGER
    	MAX-ACCESS read-only
    	STATUS current
    	DESCRIPTION
    	"
    		局端设备E1误码秒统计计数
    	"
         ::={rcftSlotStatEntry 187}

    rcftSlotE1SESCnt OBJECT-TYPE
    	SYNTAX INTEGER
    	MAX-ACCESS read-only
    	STATUS current
    	DESCRIPTION
    	"
    		局端设备E1严重误码秒统计计数
    	"
   	    ::={rcftSlotStatEntry 188}

    rcftRSlotE1ESCnt OBJECT-TYPE
    	SYNTAX INTEGER
    	MAX-ACCESS read-only
    	STATUS current
    	DESCRIPTION
    	"
    		远端设备E1误码秒统计计数
    	"
         ::={rcftSlotStatEntry 189}

    rcftRSlotE1SESCnt OBJECT-TYPE
    	SYNTAX INTEGER
    	MAX-ACCESS read-only
    	STATUS current
    	DESCRIPTION
    	"
    		远端设备E1严重误码秒统计计数
    	"
   	    ::={rcftSlotStatEntry 190}

  rcftRSlotCWDMModuleMaxSpeed OBJECT-TYPE
       	 SYNTAX INTEGER
       	 MAX-ACCESS read-only
       	 STATUS current
       	 DESCRIPTION
       	 "
       	   远端板卡cwdm侧接口模块的最大速率
         "
       	 ::={rcftSlotStatEntry 191}

  rcftRSlotCWDMModuleTransLen OBJECT-TYPE
       	SYNTAX INTEGER
       	MAX-ACCESS read-only
       	STATUS current
       	DESCRIPTION
       	"
       	 远端板卡cwdm侧SFP模块在单模光纤中的传输距离(单位为Km)
       	"
       	::={rcftSlotStatEntry 192}

   rcftRSlotCWDMModuleWaveLen OBJECT-TYPE
       	SYNTAX INTEGER
       	MAX-ACCESS read-only
       	STATUS current
       	DESCRIPTION
       	"
       	  远端板卡cwdm侧SFP模块工作波长(单位为nm)
       	"
       	::={rcftSlotStatEntry 193}

    rcftRSlotCWDMModuleManufacturer  OBJECT-TYPE
       	SYNTAX OCTET STRING(SIZE (0..30))
       	MAX-ACCESS read-only
       	STATUS current
       	DESCRIPTION
       	"
       	 远端板卡cwdm侧SFP模块的制造商
       	"
       	::={rcftSlotStatEntry 194}

   rcftRSlotCWDMModuleDescr OBJECT-TYPE
        SYNTAX OCTET STRING(SIZE (0..30))
        MAX-ACCESS read-only
        STATUS current
        DESCRIPTION
        "
          远端板卡cwdm侧产品型号
        "
        ::={rcftSlotStatEntry 195}

   rcftRSlotCWDMModuleVersion OBJECT-TYPE
        SYNTAX OCTET STRING(SIZE (0..10))
        MAX-ACCESS read-only
        STATUS current
        DESCRIPTION
        "
          远端板卡cwdm侧SFP模块的版本号
        "
        ::={rcftSlotStatEntry 196}

   rcftRSlotCWDMModuleSerialNumber OBJECT-TYPE
        SYNTAX OCTET STRING(SIZE (0..30))
        MAX-ACCESS read-only
        STATUS current
        DESCRIPTION
        "
          远端板卡cwdm侧SFP模块的序列号
        "
        ::={rcftSlotStatEntry 197}

   rcftSlotLANOPortModuleType  OBJECT-TYPE
     	  SYNTAX INTEGER
      	  {
      	     optical-M(1),
      	     optical-S1(2),
      	     optical-S2(3),
      	     optical-S3(4),
      	     optical-SS13(5),
      	     optical-SS15(6),
      	     optical-SS23(7),
      	     optical-SS25(8),
      	     optical-SS35(9),
      	     unknown-type(100)
      	  }
      	  MAX-ACCESS read-only
      	  STATUS current
      	  DESCRIPTION
      	  "
      	    板卡客户侧光口的光模块类型
      	  "
		  ::={rcftSlotStatEntry 198}

   rcftSlotWANOPortModuleType  OBJECT-TYPE
     	  SYNTAX INTEGER
      	  {
      	     optical-M(1),
      	     optical-S1(2),
      	     optical-S2(3),
      	     optical-S3(4),
      	     optical-SS13(5),
      	     optical-SS15(6),
      	     optical-SS23(7),
      	     optical-SS25(8),
      	     optical-SS35(9),
      	     unknown-type(100)
      	  }
      	  MAX-ACCESS read-only
      	  STATUS current
      	  DESCRIPTION
      	  "
      	    板卡线路侧光口的光模块类型
      	  "
		  ::={rcftSlotStatEntry 199}

    rcftSlotCDRSpeed	OBJECT-TYPE
      SYNTAX INTEGER
      {
      	  stm16-C48(1),
      	  ge-Gb(2),
      	  stm4-C12(3),
      	  stm1-C3(4),
      	  fe(5),
      	  auto(6),
      	  reserved(7)
      }
     MAX-ACCESS read-write
     STATUS current
     DESCRIPTION
     "
    	CDR的速率
     "
   	 ::={rcftSlotStatEntry 200}

    rcftRSlotManufacturer  OBJECT-TYPE
     SYNTAX OCTET STRING(SIZE (0..60))
   	 MAX-ACCESS read-only
   	 STATUS current
   	 DESCRIPTION
   	 "
   	  远端模块的制造商
   	 "
   	 ::={rcftSlotStatEntry 201}

   	rcftRSlotSoftwareVersion OBJECT-TYPE
   		SYNTAX OCTET STRING(SIZE (0..100))
   		MAX-ACCESS read-only
   		STATUS	current
   		DESCRIPTION
   		"
   			这是为RC581-FE定义的主机软件版本号
   		"
   	::={rcftSlotStatEntry 202}

      rcftRSlotVoltageValue	OBJECT-TYPE
       	SYNTAX  Unsigned32
       	MAX-ACCESS	read-only
       	STATUS	current
       	DESCRIPTION
       	"
       		这是为RC581-FE定义,每八位表示一个电压值,
       		第一个8位表示3.3V的电压值,第二个8位表示2.5V的电压值,
       		第三个8位表示1.8V的电压值,第四个高8位表示1.2V的电压值
       		--------------------------------------------
       	    |    4    |     3    |     2     |     1    |
       		--------------------------------------------

       	"
       	::={rcftSlotStatEntry 203}

    rcftRSlotCommunityRW	OBJECT-TYPE
    	SYNTAX INTEGER
    	{
    		read(1),
    		readwrite(2),
    		reserved(3)
    	}
    	MAX-ACCESS	read-only
    	STATUS 	current
    	DESCRIPTION
    	"
    		这是为RC581-FE定义的,表示当前的共同体是只读的共同体还是
    		读写共同体
    	"
        ::={rcftSlotStatEntry 204}

    rcftRSlotCommunity	OBJECT-TYPE
    	SYNTAX	OCTET STRING(SIZE (0..30))
    	MAX-ACCESS	read-only
    	STATUS	current
    	DESCRIPTION
    	"
    		这是为RC581-FE定义的,表示共同体
    	"
  	   ::={rcftSlotStatEntry 205}

   rcftRSlotDeviceIP	OBJECT-TYPE
   		SYNTAX	OCTET STRING(SIZE (0..30))
   		MAX-ACCESS	read-only
   		STATUS	current
   		DESCRIPTION
   		"
   			这是为RC581-FE定义的,表示设备的IP地址
   		"
  	   ::={rcftSlotStatEntry 206}

  	rcftSlotLinePortSpeed	OBJECT-TYPE
  		SYNTAX	INTEGER
  		MAX-ACCESS 	read-write
  		STATUS	current
  		DESCRIPTION
  		"
  			本端模块线路侧端口的工作速率
  		"
  	   ::={rcftSlotStatEntry 207}

  	rcftSlotLinePortMaxSpeed	OBJECT-TYPE
  		SYNTAX	INTEGER
  		MAX-ACCESS 	read-write
  		STATUS	current
  		DESCRIPTION
  		"
  			本端模块线路侧端口的最大工作速率
  		"
  	   ::={rcftSlotStatEntry 208}

    rcftSlotLinePortMinSpeed	OBJECT-TYPE
  		SYNTAX	INTEGER
  		MAX-ACCESS 	read-write
  		STATUS	current
  		DESCRIPTION
  		"
  			本端模块线路侧端口的最小工作速率
  		"
  	   ::={rcftSlotStatEntry 209}

      rcftSlotLinePortSNR	OBJECT-TYPE
  		SYNTAX	INTEGER
  		MAX-ACCESS 	read-write
  		STATUS	current
  		DESCRIPTION
  		"
  			本端模块线路侧端口的信噪比
  		"
  	   ::={rcftSlotStatEntry 210}

	  rcftSlotLinePortLinkUpTime	OBJECT-TYPE
	  	SYNTAX	Unsigned32
	  	MAX-ACCESS	read-only
	  	STATUS	current
	  	DESCRIPTION
	  	"
	  		本端模块线路侧端口linkup的时间
	  	"
  	   ::={rcftSlotStatEntry 211}

      rcftRSlotLinePortSNR	OBJECT-TYPE
  		SYNTAX	INTEGER
  		MAX-ACCESS 	read-write
  		STATUS	current
  		DESCRIPTION
  		"
  			远端模块线路侧端口的信噪比
  		"
  	   ::={rcftSlotStatEntry 212}

	  rcftRSlotLinePortLinkUpTime	OBJECT-TYPE
	  	SYNTAX	Unsigned32
	  	MAX-ACCESS	read-only
	  	STATUS	current
	  	DESCRIPTION
	  	"
	  		远端模块线路侧端口linkup的时间
	  	"
  	   ::={rcftSlotStatEntry 213}

      rcftRSlotLinePortSpeed	OBJECT-TYPE
  		SYNTAX	INTEGER
  		MAX-ACCESS 	read-write
  		STATUS	current
  		DESCRIPTION
  		"
  			远端模块线路侧端口的工作速率
  		"
  	   ::={rcftSlotStatEntry 214}

  	   rcftSlotOrderParameter	OBJECT-TYPE
  		SYNTAX	INTEGER
  		MAX-ACCESS 	read-write
  		STATUS	current
  		DESCRIPTION
  		"
  		    给近端模块发送命令时所需要赋的参数
  		"
  	   ::={rcftSlotStatEntry 215}

  	   rcftRSlotOrderParameter	OBJECT-TYPE
  		SYNTAX	INTEGER
  		MAX-ACCESS 	read-write
  		STATUS	current
  		DESCRIPTION
  		"
  		    给远端模块发送命令时所需要赋的参数
  		"
  	   ::={rcftSlotStatEntry 216}

       rcftSlotRevErrFluxPacket	OBJECT-TYPE
  		SYNTAX	INTEGER
  		MAX-ACCESS 	read-only
  		STATUS	current
  		DESCRIPTION
  		"
  		    用户侧侧接收错误以太网包字节数
  		"
  	   ::={rcftSlotStatEntry 217}

  	    rcftRSlotRevErrFluxPacket	OBJECT-TYPE
  		SYNTAX	INTEGER
  		MAX-ACCESS 	read-only
  		STATUS	current
  		DESCRIPTION
  		"
  		    远端用户侧侧接收错误以太网包字节数
  		"
  	   ::={rcftSlotStatEntry 218}

  	  rcftRSlotLinePortType  OBJECT-TYPE
        SYNTAX  INTEGER
		{
		   e1(1),
		   opt(2),
		   ghdsl(3),
		   reserved(10)
		}
		MAX-ACCESS read-only
		STATUS     current
		DESCRIPTION
		"
		  	上行接口类型
		"
  	   ::={rcftSlotStatEntry 219}

  	 rcftRSlotManageChannelSel OBJECT-TYPE
		SYNTAX  INTEGER
		{
		    aloneTimeSlot(1),
		    optChannels(2),
		    saChannels(3)
		}
		MAX-ACCESS read-write
		STATUS     current
		DESCRIPTION
		"
		  	网管通道选择(1:使用独立时隙作通道 2:使用光通道 3: 使用SA通道)
		"
       ::={rcftSlotStatEntry 220}

    rcftRSlotManageChannelTSNum OBJECT-TYPE
		SYNTAX INTEGER
		MAX-ACCESS read-write
		STATUS     current
		DESCRIPTION
		"
 		-- 使用独立时隙作通道时,只能有一个时隙做为网管通道,
 		-- 其中0时隙不能占用,在成帧模式为PCM30时,不能占用16时隙
		-- 编号规则:
		-- 4个字节表示时隙的占用情况,编码规则:
        -----------------------------------
        | bit31 bit30 bit29 ... bit1 bit0 |
        | TS31  TS30  TS29  ... TS1  TS0  |
        -----------------------------------
        -- 0:空闲,1:占用
		"
      ::={rcftSlotStatEntry 221}

      rcftRSlotV35TimeSlots OBJECT-TYPE
		SYNTAX Unsigned32
		MAX-ACCESS read-write
		STATUS current
		DESCRIPTION
		"
        -- 占用时隙信息,其中0时隙不能占用,
 		-- 在成帧模式为PCM30时,不能占用16时隙
		-- 编号规则:
		-- 4个字节表示时隙的占用情况,编码规则:
        -----------------------------------
        | bit31 bit30 bit29 ... bit1 bit0 |
        | TS31  TS30  TS29  ... TS1  TS0  |
        -----------------------------------
        -- 0:空闲,1:占用
		"
        ::={rcftSlotStatEntry 222}

      rcftSlotLinePortSNRConf OBJECT-TYPE
  		SYNTAX	INTEGER
  		MAX-ACCESS 	read-write
  		STATUS	current
  		DESCRIPTION
  		"
  			本端模块线路侧端口配置的信噪比
  		"
  	   ::={rcftSlotStatEntry 223}

    rcftRSlotLANOPortModuleType  OBJECT-TYPE
     	  SYNTAX INTEGER
      	  {
      	     optical-M(1),
      	     optical-S1(2),
      	     optical-S2(3),
      	     optical-S3(4),
      	     optical-SS13(5),
      	     optical-SS15(6),
      	     optical-SS23(7),
      	     optical-SS25(8),
      	     optical-SS35(9),
      	     unknown-type(100)
      	  }
      	  MAX-ACCESS read-only
      	  STATUS current
      	  DESCRIPTION
      	  "
      	    远端板卡客户侧光口的光模块类型
      	  "
		  ::={rcftSlotStatEntry 224}

	rcftRSlotConfigFlag		OBJECT-TYPE
		SYNTAX	INTEGER
		MAX-ACCESS read-write
		STATUS	current
		DESCRIPTION
		"
		--该对象目前是针对RC3101板卡增加的.RC3101板卡配置信息
		--较多,需要分块进行配置
		--编码规则,每一位代表当前对某一块信息进行配置
		-- 约定:
		-- bit0: 系统信息配置
		-- bit1: 语音配置1
		-- bit2: 语音配置2
		-- bit3: V35数据块配置
		-- bit4: ETH数据配置
        -----------------------------------
        | bit31 bit30 bit29 ... bit1 bit0 |
        -----------------------------------
		"
  	     ::={rcftSlotStatEntry 225}

    rcftSlotOpticalDeviceStatus OBJECT-TYPE
      SYNTAX INTEGER
        MAX-ACCESS read-write
        STATUS current
        DESCRIPTION
          "
          	模块的光器件类型和状态
          "
	::= {rcftSlotStatEntry 226}

    rcftSlotPrimaryAdjustFactor OBJECT-TYPE
       	SYNTAX INTEGER
       	MAX-ACCESS read-only
       	STATUS current
       	DESCRIPTION
       	"
       	  主用光通道光功率校准系数，应为45-61之间的数字
       	"
       	::={rcftSlotStatEntry 227}

    rcftSlotPrimaryOpticalRate OBJECT-TYPE
       	SYNTAX OCTET STRING(SIZE (0..10))
       	MAX-ACCESS read-only
       	STATUS current
       	DESCRIPTION
       	"
       	 主用光通道光功率
       	"
       	::={rcftSlotStatEntry 228}

    rcftSlotPrimaryTrapThreshold OBJECT-TYPE
       	SYNTAX OCTET STRING(SIZE (0..10))
       	MAX-ACCESS read-write
       	STATUS current
       	DESCRIPTION
       	"
       	 主用光通道告警阈值
       	"
       	::={rcftSlotStatEntry 229}

    rcftSlotSecondaryAdjustFactor OBJECT-TYPE
       	SYNTAX INTEGER
       	MAX-ACCESS read-only
       	STATUS current
       	DESCRIPTION
       	"
       	  备用光通道光功率校准系数，应为45-61之间的数字
       	"
       	::={rcftSlotStatEntry 230}

    rcftSlotSecondaryOpticalRate OBJECT-TYPE
       	SYNTAX OCTET STRING(SIZE (0..10))
       	MAX-ACCESS read-only
       	STATUS current
       	DESCRIPTION
       	"
          备用光通道光功率
       	"
       	::={rcftSlotStatEntry 231}

    rcftSlotSecondaryTrapThreshold OBJECT-TYPE
       	SYNTAX OCTET STRING(SIZE (0..10))
       	MAX-ACCESS read-write
       	STATUS current
       	DESCRIPTION
       	"
          备用光通道告警阈值
       	"
       	::={rcftSlotStatEntry 232}


  	rcftSlotWANSendErrFluxPacket OBJECT-TYPE
  		SYNTAX INTEGER
  		MAX-ACCESS read-only
  		STATUS 	current
  		DESCRIPTION
  		"
  			本端模块线路侧发送失败帧数
  		"
  		 ::={rcftSlotStatEntry 233}


	rcftRSlotWANSendErrFluxPacket  OBJECT-TYPE
		SYNTAX	INTEGER
		MAX-ACCESS	read-only
		STATUS	current
		DESCRIPTION
		"
			远端模块线路侧发送失败帧数
		"
	     ::={rcftSlotStatEntry 234}

  	 rcftSlotOpticalDeviceType OBJECT-TYPE
		SYNTAX  INTEGER
		{
		    splitter-50-50(1),
		    wdm-1310nm-1550nm(2),
		    fwdm-1550nm(3),
		    cwdm-1490nm(4)
		}
		MAX-ACCESS read-only
		STATUS     current
		DESCRIPTION
		"
		  	光器件类型
		  	 (1)50:50光分路器
		  	 (2)波分复用器1310/1550nm；
             (3)光纤到户滤波器1550nm；
             (4)粗波分复用器1490nm;
		"
         ::={rcftSlotStatEntry 235}

    rcftRSlotCardOrderInfor OBJECT-TYPE
       	SYNTAX OCTET STRING(SIZE (0..80))
       	MAX-ACCESS read-only
       	STATUS current
       	DESCRIPTION
       	"
           设备的订货信息。
       	"
       	::={rcftSlotStatEntry 236}

    rcftRSlotTimeSlots	OBJECT-TYPE
	  	SYNTAX OCTET STRING(SIZE (4..16))
	  	MAX-ACCESS	read-write
	  	STATUS	current
	  	DESCRIPTION
	  	"
	  	   设备总的时隙占用情况
        -- 占用时隙信息，其中0时隙不能占用，
 		-- 在成帧模式为PCM30时，不能占用16时隙

           其中第1到第4字节是第一路E1时隙的占用情况，
           第5到第8字节是第二路E1时隙的占用情况，
           第9到第12字节是第三路E1的时隙占用情况，
           第13到第16字节是第四路E1的时隙占用情况
	  	"
  	   ::={rcftSlotStatEntry 237}

  	 rcftRSlotServiceConnectMode OBJECT-TYPE
		SYNTAX  INTEGER
		{
            mode1(1),
		    mode2(2),
		    mode3(3),
		    reserve(4)
		}
		MAX-ACCESS read-write
		STATUS     current
		DESCRIPTION
		"
		  设备的互通模式：
		  	1：和RC3101等对通
            2：和RJ107对通
            3：和RC3000、906对通
            4：保留模式
		"
         ::={rcftSlotStatEntry 238}

     rcftSlotSendErrFluxPacket    OBJECT-TYPE
     	SYNTAX	INTEGER
     	MAX-ACCESS read-only
     	STATUS 	current
     	DESCRIPTION
     	"
     		客户侧发送失败帧数
     	"
	    ::={rcftSlotStatEntry 239}

     rcftRSlotSendErrFluxPacket    OBJECT-TYPE
     	SYNTAX	INTEGER
     	MAX-ACCESS read-only
     	STATUS 	current
     	DESCRIPTION
     	"
     		远端模块客户侧发送失败帧数
     	"
	    ::={rcftSlotStatEntry 240}

       cwdmSecondaryCWDMModuleMaxSpeed OBJECT-TYPE
       	 SYNTAX INTEGER
       	 MAX-ACCESS read-only
       	 STATUS current
       	 DESCRIPTION
       	 "
       	   cwdm侧备用通道的接口模块的最大速率
         "
       	 ::={rcftSlotStatEntry 241}

       cwdmSecondaryCWDMModuleTransLen OBJECT-TYPE
       	SYNTAX INTEGER
       	MAX-ACCESS read-only
       	STATUS current
       	DESCRIPTION
       	"
       	 cwdm侧备用通道的SFP模块在单模光纤中的传输距离(单位为Km)
       	"
       	::={rcftSlotStatEntry 242}

       cwdmSecondaryCWDMModuleWaveLen OBJECT-TYPE
       	SYNTAX INTEGER
       	MAX-ACCESS read-only
       	STATUS current
       	DESCRIPTION
       	"
       	  cwdm侧备用通道的SFP模块工作波长(单位为nm)
       	"
       	::={rcftSlotStatEntry 243}

       cwdmSecondaryCWDMModuleManufacturer  OBJECT-TYPE
       	SYNTAX OCTET STRING(SIZE (0..30))
       	MAX-ACCESS read-only
       	STATUS current
       	DESCRIPTION
       	"
       	 cwdm侧备用通道的SFP模块的制造商
       	"
       	::={rcftSlotStatEntry 244}

       cwdmSecondaryCWDMModuleDescr OBJECT-TYPE
        SYNTAX OCTET STRING(SIZE (0..30))
        MAX-ACCESS read-only
        STATUS current
        DESCRIPTION
        "
          cwdm侧备用通道的产品型号
        "
        ::={rcftSlotStatEntry 245}

       cwdmSecondaryCWDMModuleVersion OBJECT-TYPE
        SYNTAX OCTET STRING(SIZE (0..10))
        MAX-ACCESS read-only
        STATUS current
        DESCRIPTION
        "
          cwdm侧备用通道的SFP模块的版本号
        "
        ::={rcftSlotStatEntry 246}

       cwdmSecondaryCWDMModuleSerialNumber OBJECT-TYPE
        SYNTAX OCTET STRING(SIZE (0..30))
        MAX-ACCESS read-only
        STATUS current
        DESCRIPTION
        "
          cwdm侧备用通道的SFP模块的序列号
        "
        ::={rcftSlotStatEntry 247}

	    rcftSlotVLANTagDirection OBJECT-TYPE
	        SYNTAX INTEGER
	        {
	           fxtotx(1),
	           txtofx(2)
	        }
	        MAX-ACCESS read-write
	        STATUS current
	        DESCRIPTION
	          "
	          	局端设备的VLAN-TAG方向:(1:光口到电口,2:电口到光口).
	          "
		::= {rcftSlotStatEntry 248}

	    rcftRSlotVLANTagDirection OBJECT-TYPE
	        SYNTAX INTEGER
	        {
	           fxtotx(1),
	           txtofx(2)
	        }
	        MAX-ACCESS read-write
	        STATUS current
	        DESCRIPTION
	          "
	          	远端设备的VLAN-TAG方向:(1:光口到电口,2:电口到光口).
	          "
		::= {rcftSlotStatEntry 249}

	    rcftSlotVLANTagModule	OBJECT-TYPE
	      SYNTAX INTEGER
	      {
	      	  notag(1),
	      	  onetag(2),
	      	  twotag(3),
	      	  reserve(4)
	      }
	     MAX-ACCESS read-write
	     STATUS current
	     DESCRIPTION
	     "
	    	 局端设备的VLAN-TAG模式:(1:透传,2:单TAG,3:双TAG,无效保留).
	     "
	   	 ::={rcftSlotStatEntry 250}

	    rcftRSlotVLANTagModule	OBJECT-TYPE
	      SYNTAX INTEGER
	      {
	      	  notag(1),
	      	  onetag(2),
	      	  twotag(3),
	      	  reserve(4)
	      }
	     MAX-ACCESS read-write
	     STATUS current
	     DESCRIPTION
	     "
	    	 远端设备的VLAN-TAG模式:(1:透传,2:单TAG,3:双TAG,无效保留).
	     "
	   	 ::={rcftSlotStatEntry 251}

	  	rcftSlotVLANID	OBJECT-TYPE
	  		SYNTAX	INTEGER
	  		MAX-ACCESS 	read-write
	  		STATUS	current
	  		DESCRIPTION
	  		"
	  			局端设备的VLAN ID
	  		"
	  	   ::={rcftSlotStatEntry 252}

	  	rcftRSlotVLANID	OBJECT-TYPE
	  		SYNTAX	INTEGER
	  		MAX-ACCESS 	read-write
	  		STATUS	current
	  		DESCRIPTION
	  		"
	  			远端设备的VLAN ID
	  		"
	  	   ::={rcftSlotStatEntry 253}

	  	rcftSlotISPTPID	OBJECT-TYPE
	  		SYNTAX	INTEGER
	  		MAX-ACCESS 	read-write
	  		STATUS	current
	  		DESCRIPTION
	  		"
	  			局端设备的ISP TPID
	  		"
	  	   ::={rcftSlotStatEntry 254}

	  	rcftRSlotISPTPID	OBJECT-TYPE
	  		SYNTAX	INTEGER
	  		MAX-ACCESS 	read-write
	  		STATUS	current
	  		DESCRIPTION
	  		"
	  			远端设备的ISP TPID
	  		"
	  	   ::={rcftSlotStatEntry 255}

	  rcftSlotE1SubCardType	OBJECT-TYPE
	  		SYNTAX	INTEGER
	  		MAX-ACCESS 	read-only
	  		STATUS	current
	  		DESCRIPTION
	  		"
	  			局端设备的E1子卡类型

	  			数值和设备的对应关系是：
	  			0： RC2002-SUB_1E1
				1： RC2002-SUB_2E1
				2： RC954－SUB－4E1－BL
				3： RC954－SUB－8E1－BL
				4： RC2802-SUB-4E1
				5： RC832-SUB-8E1
				6： RC832-SUB-8E1-BL
				7： RC832-SUB-4E1-BL
				8： RC954－SUB－8E1
	  		"
	  	   ::={rcftSlotStatEntry 256}

	  rcftSlotMultiE1LoopOrder	OBJECT-TYPE
	  		SYNTAX	OCTET STRING(SIZE (0..64))
			MAX-ACCESS	read-write
			STATUS	current
			DESCRIPTION
			"
			   E1环回的命令，每一字节表示一路E1的环回命令
			   0:本地环回使能，1：解除本地环回：，2：远端环回使能，3：解除远端环回
			"
            ::={rcftSlotStatEntry 257}

     rcftSlotSubModuleExist	OBJECT-TYPE
     	SYNTAX	INTEGER
     	MAX-ACCESS read-only
     	STATUS	current
     	DESCRIPTION
     	"
     		每一位表示扩展槽N子卡的在位状态：0：不在位，1：在位
     	"
   	    ::={rcftSlotStatEntry 258}

  	 rcftSlotOrderTimeParameter	OBJECT-TYPE
  		 SYNTAX	INTEGER
  		 MAX-ACCESS 	read-write
  		 STATUS	current
  		 DESCRIPTION
  		 "
  		    给局端模块发送命令时所需要赋的时长参数。

  		    1: 测试时长1分钟
  		    2: 测试时长2分钟
  		    3: 测试时长4分钟
  		    4: 测试时长8分钟
  		    5: 测试时长15分钟
  		    6: 测试时长30分钟
  		    7: 测试时长60分钟

  		    18: 测试2帧
  		    19: 测试5帧
  		    20: 测试10帧
  		    21: 测试20帧
  		    22: 测试50帧
  		    23: 测试100帧
  		"
  	   	::={rcftSlotStatEntry 259}

  	rcftSlotRLPStatus	OBJECT-TYPE
  		 SYNTAX	INTEGER
  		 MAX-ACCESS 	read-only
  		 STATUS	current
  		 DESCRIPTION
  		 "
  		   	RLP指示灯状态
  		   	1：RLP灯灭
			2：RLP绿闪
			3：RLP绿常亮
			4：RLP黄闪
			5：RLP黄常亮
  		 "
 	     ::={rcftSlotStatEntry 260}

  	rcftSlotSFPDiagnosticsInfo	OBJECT-TYPE
  		 SYNTAX	INTEGER
  		 MAX-ACCESS 	read-only
  		 STATUS	current
  		 DESCRIPTION
  		 "
     		局端模块数字诊断的相关信息

     		bit13: 收光功率下限告警：  1：有告警，0：没有告警
     		bit12: 收光功率上限告警：  1：有告警，0：没有告警
     		bit11: 发光功率下限告警：  1：有告警，0：没有告警
     		bit10: 发光功率上限告警：  1：有告警，0：没有告警
     		bit9: 电流下限告警：  1：有告警，0：没有告警
     		bit8: 电流上限告警：  1：有告警，0：没有告警
     		bit7: 电压下限告警：  1：有告警，0：没有告警
     		bit6: 电压上限告警：  1：有告警，0：没有告警
     		bit5: 温度下限告警：  1：有告警，0：没有告警
     		bit4: 温度上限告警：  1：有告警，0：没有告警
     		bit3: SFP模块是否有告警：  1：有告警，0：没有告警
     		bit2: 是否具有数字诊断功能：1：有 0：无
      		bit1: 远端是否有严重事件告警：  1：有告警，0：没有告警
     		bit0: 是否建立OAM连接： 1：建立连接，0：未建立连接

  		 "
 	     ::={rcftSlotStatEntry 261}

	rcftRSlotSFPDiagnosticsInfo  		OBJECT-TYPE
  		 SYNTAX	INTEGER
  		 MAX-ACCESS 	read-only
  		 STATUS	current
  		 DESCRIPTION
  		 "
     		远端模块数字诊断的相关信息

     		bit13: 收光功率下限告警：  1：有告警，0：没有告警
     		bit12: 收光功率上限告警：  1：有告警，0：没有告警
     		bit11: 发光功率下限告警：  1：有告警，0：没有告警
     		bit10: 发光功率上限告警：  1：有告警，0：没有告警
     		bit9: 电流下限告警：  1：有告警，0：没有告警
     		bit8: 电流上限告警：  1：有告警，0：没有告警
     		bit7: 电压下限告警：  1：有告警，0：没有告警
     		bit6: 电压上限告警：  1：有告警，0：没有告警
     		bit5: 温度下限告警：  1：有告警，0：没有告警
     		bit4: 温度上限告警：  1：有告警，0：没有告警
     		bit3: SFP模块是否有告警：  1：有告警，0：没有告警
     		bit2: 是否具有数字诊断功能：1：有 0：无
      		bit1: 远端是否有严重事件告警：  1：有告警，0：没有告警
     		bit0: 是否建立OAM连接： 1：建立连接，0：未建立连接

  		 "
 	     ::={rcftSlotStatEntry 262}

    rcftSlotTemp OBJECT-TYPE
        SYNTAX INTEGER
        MAX-ACCESS read-only
        STATUS current
        DESCRIPTION
          "
          	局端模块的温度,单位为摄氏度.
          "
        ::= { rcftSlotStatEntry 263 }

    rcftSlotLALStatus	OBJECT-TYPE
    	SYNTAX INTEGER
    	MAX-ACCESS read-only
    	STATUS current
    	DESCRIPTION
    	"
    	 	0: 灭
    	 	1:黄闪亮
    	 	2:黄常亮
    	 	3:红闪亮
    	 	4:红常亮

    	"
    	::= { rcftSlotStatEntry 264 }

     rcftSlotRALStatus	OBJECT-TYPE
    	SYNTAX INTEGER
    	MAX-ACCESS read-only
    	STATUS current
    	DESCRIPTION
    	"
    	 	0: 灭
    	 	1:黄闪亮
    	 	2:黄常亮
    	 	3:红闪亮
    	 	4:红常亮

    	"
        ::= { rcftSlotStatEntry 265 }

    rcftSlotCardInformation    OBJECT-TYPE
    	SYNTAX OCTET STRING(SIZE (0..30))
       	MAX-ACCESS read-only
       	STATUS current
       	DESCRIPTION
       	"
    		订货信息，
    		对于光端机来说： 例如：RCMS1000-604AL-XXXX 。
    			其中：XXXX表示4个扩展槽的小模块是否存在及类型。每个X表示一个槽位是否存在小模块：
				０：无，Ｄ：有数据，Ａ：有音频，Ｖ：有视频，E：有以太口，1：有非智能

    	"
    	::= {rcftSlotStatEntry 266}

		rcftSlotVoltage OBJECT-TYPE
    	SYNTAX INTEGER
    	MAX-ACCESS read-only
    	STATUS current
    	DESCRIPTION
		"
			工作电压
		"
		::= {rcftSlotStatEntry 267}

		rcftSlotVoltageHighLimit OBJECT-TYPE
    	SYNTAX INTEGER
    	MAX-ACCESS read-write
    	STATUS current
    	DESCRIPTION
		"
			工作电压上限值
		"
		::= {rcftSlotStatEntry 268}

		rcftSlotVoltageLowLimit	OBJECT-TYPE
    	SYNTAX INTEGER
    	MAX-ACCESS read-write
    	STATUS current
    	DESCRIPTION
		"
			工作电压下限值
		"
		::= {rcftSlotStatEntry 269}

		rcftSlotTempHighLimit	OBJECT-TYPE
    		SYNTAX INTEGER
    		MAX-ACCESS read-write
    		STATUS current
    		DESCRIPTION
			"
				工作温度上限值
			"
			::= {rcftSlotStatEntry 270}

		rcftSlotTempLowLimit OBJECT-TYPE
    		SYNTAX INTEGER
    		MAX-ACCESS read-write
    		STATUS current
    		DESCRIPTION
			"
				工作温度下限值
			"
			::= {rcftSlotStatEntry 271}

		rcftSlotHumidity	OBJECT-TYPE
    		SYNTAX INTEGER
    		MAX-ACCESS read-only
    		STATUS current
    		DESCRIPTION
			"
				工作湿度值
			"
			::= {rcftSlotStatEntry 272}

		rcftSlotHumidityHighLimit OBJECT-TYPE
    		SYNTAX INTEGER
    		MAX-ACCESS read-write
    		STATUS current
    		DESCRIPTION
			"
				工作温度上限值
			"
			::= {rcftSlotStatEntry 273}


		rcftSlotHumidityLowLimit	OBJECT-TYPE
    		SYNTAX INTEGER
    		MAX-ACCESS read-write
    		STATUS current
    		DESCRIPTION
			"
				工作温度下限值
			"
			::= {rcftSlotStatEntry 274}


		rcftSlotMultiE1AlarmRejectOrder	OBJECT-TYPE
	  		SYNTAX	OCTET STRING(SIZE (0..64))
			MAX-ACCESS	read-write
			STATUS	current
			DESCRIPTION
			"
			   E1告警屏蔽命令，每一字节表示一路E1的告警屏蔽
			   1：屏蔽
			   2：不屏蔽
			"
            ::={rcftSlotStatEntry 275}

        rcftT1PortPulseWaveForm		OBJECT-TYPE
	   		SYNTAX INTEGER
	   		MAX-ACCESS	read-write
	   		STATUS	current
	   		DESCRIPTION
	   		"
	   			 T1 脉冲波形

	   			 2：T1传输距离为0~133ft
				 3：T1传输距离为133~266ft
				 4：T1传输距离为266~399ft
				 5：T1传输距离为399~533ft
				 6：T1传输距离为533~655ft
	   		"
	   		::= {rcftSlotStatEntry 276}

        rcftT1PortCodeType	OBJECT-TYPE
	   		SYNTAX INTEGER
	   		MAX-ACCESS	read-write
	   		STATUS	current
	   		DESCRIPTION
	   		"
	   			T1的编码类型
	   			1：B8ZS
	   			2：AMI
	   		"
	   		::= {rcftSlotStatEntry 277}

	   	rcftSlotSDRAM   OBJECT-TYPE
	   		SYNTAX INTEGER
	   		MAX-ACCESS	read-write
	   		STATUS	current
	   		DESCRIPTION
	   		"
	   			缓存大小
	   			1：全用		2：半用		3：四分之一占用		4：八分之一占用
			"
	   		::= {rcftSlotStatEntry 278}

		rcftSlotSabitMode  OBJECT-TYPE
	   		SYNTAX INTEGER
	   		MAX-ACCESS	read-write
	   		STATUS	current
	   		DESCRIPTION
			"
				rcftSlotSabitMode：
				bit1-0：Sa4
				bit3-2：Sa5
				bit5-4：Sa6
				bit7-6：Sa7
				bit9-8：Sa8

				00：字节模式
				01：HDLC模式
				10：禁止使用
			"
	   		::= {rcftSlotStatEntry 279}

        rcftSlotApsWaitToRestore OBJECT-TYPE
	   		SYNTAX INTEGER (0..255)
	   		MAX-ACCESS read-write
	   		STATUS current
	   		DESCRIPTION
	   		"
	   			-- 设备保护倒换自恢复时间，恢复到主通道的时间,以分钟为单位
	   			-- 缺省值为12min，可以设置范围为0－255min
	   		"
	   		::= { rcftSlotStatEntry 280 }

	   	rcftSlotCLKChannel  OBJECT-TYPE
	   		SYNTAX INTEGER
	   		MAX-ACCESS	read-write
	   		STATUS	current
	   		DESCRIPTION
	   		"
	   		    从时钟选取的E1编号，范围：1-设备E1端口数
			"
	   		::= {rcftSlotStatEntry 281}

	   	rcftSlotRmcChannelType	 OBJECT-TYPE
	   		SYNTAX INTEGER
	   		MAX-ACCESS	read-write
	   		STATUS	current
	   		DESCRIPTION
	   		"
	   		     收发器网管通道模式：1：802.3ah，2：rclink, 3:TS1000,	10:远端收发器网管禁止
			"
	   		::= {rcftSlotStatEntry 282}

	   	rcftSlotApsE3SwitchDelay OBJECT-TYPE
	   		SYNTAX INTEGER
	   		MAX-ACCESS read-write
	   		STATUS current
	   		DESCRIPTION
	   		"
            	设备保护倒换时，E-3告警切换延时时间，以秒为单位
            	1～15，默认为5
	   		"
	   		::= { rcftSlotStatEntry 283 }

 	   	rcftSlotApsE6SwitchDelay OBJECT-TYPE
	   		SYNTAX INTEGER
	   		MAX-ACCESS read-write
	   		STATUS current
	   		DESCRIPTION
	   		"
            	设备保护倒换时，E-6告警切换延时时间，以秒为单位
            	1～255，默认为60
	   		"
	   		::= { rcftSlotStatEntry 284 }

 	   	rcftE1DS1PortType OBJECT-TYPE
	   		SYNTAX INTEGER
	   		MAX-ACCESS read-write
	   		STATUS current
	   		DESCRIPTION
	   		"
	   			E1/DS1（T1）模式。	 0：E1，1：DS1（T1）
	   		"
	   		::= { rcftSlotStatEntry 285 }

 	   rcftSlotManageID OBJECT-TYPE
	   		SYNTAX INTEGER
	   		MAX-ACCESS read-write
	   		STATUS current
	   		DESCRIPTION
	   		"
	   			设备管理ID。	 1~255
	   		"
	   		::= { rcftSlotStatEntry 286 }

 	   rcftSlotE1PortNumber OBJECT-TYPE
	   		SYNTAX INTEGER
	   		MAX-ACCESS read-only
	   		STATUS current
	   		DESCRIPTION
	   		"
	   			E1支路数量。	 1～32
	   		"
	   		::= { rcftSlotStatEntry 287 }

       rcftSlotQoS OBJECT-TYPE
       		SYNTAX INTEGER
       		MAX-ACCESS read-write
       		STATUS current
       		DESCRIPTION
       		"
       			 1：使能，2：禁止
       		"
       		::= {rcftSlotStatEntry 288}

        rcftSlotTPIDRemark OBJECT-TYPE
       		SYNTAX INTEGER
       		MAX-ACCESS read-write
       		STATUS current
       		DESCRIPTION
       		"
       			 1：使能，2：禁止
       		"
       		::= {rcftSlotStatEntry 289}
       rcftRSlotTPIDRemark OBJECT-TYPE
       		SYNTAX INTEGER
       		MAX-ACCESS read-write
       		STATUS current
       		DESCRIPTION
       		"
       			 1：使能，2：禁止
       		"
       		::= {rcftSlotStatEntry 290}

       rcftSlotDeviceMibUse OBJECT-TYPE
       		SYNTAX INTEGER
       		{
	      		mib002(1),
	      		rccomlib(2)
	      	}

       		MAX-ACCESS read-only
       		STATUS current
       		DESCRIPTION
       		"
       			 设备支持的mib类型
       			1:使用002mib
			2:使用组件库mib

       		"
       		::= {rcftSlotStatEntry 291}
      rcftSlotApsSwitchDelay OBJECT-TYPE
	       SYNTAX INTEGER (0..255)
	       MAX-ACCESS read-write
	       STATUS current
	       DESCRIPTION
	       "
	   	    -- 设备保护倒换切换延迟时间，有损模式二下有效,以100ms为单位
	      	-- 缺省值为0，可以设置范围为0－60
	       "
	       ::= { rcftSlotStatEntry 292 }

    rcftInterfaceStatTable OBJECT-TYPE
        SYNTAX SEQUENCE OF RcftInterfaceStatEntry
        MAX-ACCESS not-accessible
        STATUS current
        DESCRIPTION
          " The table holding information related to the remote eth port status."
        ::= {rcftSlotStat 2}

    rcftInterfaceStatEntry OBJECT-TYPE
        SYNTAX RcftInterfaceStatEntry
        MAX-ACCESS not-accessible
        STATUS current
        DESCRIPTION
          "  "
        INDEX { rcftChassisIndex, rcftSlotIndex, rcftInterfaceType, rcftInterfaceIndex}
        ::= {rcftInterfaceStatTable 1}

    RcftInterfaceStatEntry ::= SEQUENCE {

           rcftInterfaceType
                INTEGER,
            rcftInterfaceIndex
                INTEGER,
            rcftInterfaceRLink
                INTEGER,
            rcftInterfaceRAutoNegotiation
                INTEGER,
            rcftInterfaceRDuplex
                INTEGER,
            rcftInterfaceRSpeed
                INTEGER,
            rcftInterfaceRStat
                INTEGER,
            rcftInterfaceLOS
            	INTEGER,
            rcftInterfaceCV
            	INTEGER,
            rcftInterfaceAIS
            	INTEGER,
            rcftInterfaceLOF
            	INTEGER,
            rcftInterfaceCRC
            	INTEGER,
            rcftInterfaceE5
            	INTEGER,
            rcftInterfaceRLOS
            	INTEGER,
            rcftInterfaceRCV
            	INTEGER,
            rcftInterfaceRAIS
            	INTEGER,
            rcftInterfaceRLOF
            	INTEGER,
            rcftInterfaceRCRC
            	INTEGER,
            rcftInterfaceUnUsed
            	INTEGER,
            rcftInterfaceStat
                INTEGER,
            rcftInterfaceLink
                INTEGER,
            rcftInterfaceAutoNegotiation
                INTEGER,
            rcftInterfaceDuplex
                INTEGER,
            rcftInterfaceSpeed
                INTEGER,
            rcftInterfaceTag
                INTEGER,
            rcftInterfaceRecvRestrictSpeed
            	INTEGER,
            rcftInterfaceSendRestrictSpeed
            	INTEGER,
            rcftInterfaceRTag
            	INTEGER,
            rcftInterfaceRRecvFluxCount
            	INTEGER,
         	rcftInterfaceRSendFluxCount
         		INTEGER,
			rcftInterfaceRRecvFluxTimer
				Counter32,
			rcftInterfaceRSendFluxTimer
				Counter32,
			rcftInterfaceRpriority
				INTEGER,
			rcftInterfaceRMDIXAuto
				INTEGER,
			rcftInterfaceRRecvRestrictSpeed
				INTEGER,
			rcftInterfaceRFlowCtrl
				INTEGER,
			rcftInterfaceRAudioType
				INTEGER,
			rcftInterfaceRAudioTimeSlots
				Unsigned32,
			rcftInterfaceRAudioInSignalingSymbol
				INTEGER,
			rcftInterfaceRAudioOutSignalingSymbol
				INTEGER,
			rcftInterfaceRAudioInSignalingType
				INTEGER,
			rcftInterfaceRAudioOutSignalingType
				INTEGER,
			rcftInterfaceRAudioInSignalingStatus
				INTEGER,
			rcftInterfaceRAudioOutSignalingStatus
				INTEGER,
			rcftInterfaceRAudioUseEnable
				INTEGER,
			rcftInterfaceWANToLANFPEnWANDownLANPortStatus
				INTEGER,
			rcftInterfaceWANTOLANFPEnRemoteLANDownLANPortStatus
				INTEGER,
			rcftInterfaceRecvFluxCount
				INTEGER,
			rcftInterfaceSendFluxCount
				INTEGER,
			rcftInterfaceRecvFluxPacket
				INTEGER,
			rcftInterfaceSendFluxPacket
				INTEGER,
			rcftInterfaceRecvErrFluxPacket
				INTEGER,
			rcftInterfaceSendErrFluxPacket
				INTEGER,
			rcftInterfaceRecvFluxTimer
				Counter32,
			rcftInterfaceSendFluxTimer
				Counter32,
			rcftInterfaceRSendRestrictSpeed
				INTEGER,
			rcftInterfaceRWANToLANFPEnWANDownLANPortStatus
				INTEGER,
			rcftInterfaceRWANTOLANFPEnRemoteLANDownLANPortStatus
				INTEGER,
			rcftInterfaceRRecvFluxPacket
				INTEGER,
			rcftInterfaceRSendFluxPacket
				INTEGER,
			rcftInterfaceRRecvErrFluxPacket
				INTEGER,
			rcftInterfaceRSendErrFluxPacket
				INTEGER,
			rcftInterfaceFoundLink
				INTEGER,
			rcftInterfaceBERT
				INTEGER,
			rcftInterfaceCLKMode
				INTEGER,
			rcftInterfaceCRCStatus
				INTEGER,
			rcftInterfaceCRCEnable
				INTEGER,
			rcftInterfaceLocalLoopEn
				INTEGER,
			rcftInterfaceRemoteLoopEn
				INTEGER,
			rcftInterfaceTransErrorCode
				INTEGER,
			rcftInterfaceE1Location
				INTEGER,
			rcftInterfaceE1ESCnt
				INTEGER,
			rcftInterfaceE1SESCnt
				INTEGER,
			rcftInterfaceE1TimeSlot
				Unsigned32,
			rcftInterfaceE1Transparent
				INTEGER
    }

    rcftInterfaceType OBJECT-TYPE
        SYNTAX INTEGER{
               ethport(1),
               audioChannel(2),
               e1port(3)
       }
        MAX-ACCESS read-only
        STATUS current
        DESCRIPTION
          "
          	接口类型(1:电口,2:语音信道,3:E1口)
          "
        ::= {rcftInterfaceStatEntry 1}

    rcftInterfaceIndex OBJECT-TYPE
        SYNTAX INTEGER(1..16)
        MAX-ACCESS read-only
        STATUS current
        DESCRIPTION
          "
          	接口索引(1-16)
          "
        ::= {rcftInterfaceStatEntry 2}

    rcftInterfaceRLink OBJECT-TYPE
        SYNTAX INTEGER
        {
            link-up(1),
            link-down(2)
        }
        MAX-ACCESS read-only
        STATUS current
        DESCRIPTION
          "
          	远端接口LINK(1:link-up, 2:link-down)
          "
        ::= {rcftInterfaceStatEntry 3}

    rcftInterfaceRAutoNegotiation OBJECT-TYPE
        SYNTAX INTEGER
        {
            auto(1),
            manul(2)
        }
        MAX-ACCESS read-write
        STATUS current
        DESCRIPTION
          "
          	远端接口速率协商状态(1:自协商,2:手动)
          "
        ::= {rcftInterfaceStatEntry 4}

    rcftInterfaceRDuplex OBJECT-TYPE
        SYNTAX INTEGER
        {
            full-duplex(1),
            half-duplex(2),
            auto(3)
        }
        MAX-ACCESS read-write
        STATUS current
        DESCRIPTION
          "
          	远端接口双工状态(1:全双工,2:半双工,3:自动)
          "
        ::= {rcftInterfaceStatEntry 5}

    rcftInterfaceRSpeed OBJECT-TYPE
        SYNTAX INTEGER
        {
            rcft10Mbps(1),
            rcft100Mbps(2),
            rcft1000Mbps(3),
            rcft10Gbps(4),
            other(16)
        }
        MAX-ACCESS read-write
        STATUS current
        DESCRIPTION
          "
       	远端接口速率(1:10Mbps,2:100Mbps,3:1000Mbps,4:10Gbps,16:其他)
          "
        ::= {rcftInterfaceStatEntry 6}

    rcftInterfaceRStat OBJECT-TYPE
        SYNTAX INTEGER
        {
            open(1),
            close(2)
        }
        MAX-ACCESS read-write
        STATUS current
        DESCRIPTION
          "
          	远端接口状态:(1:打开,2:关闭)
          "
        ::= {rcftInterfaceStatEntry 7}

    rcftInterfaceLOS OBJECT-TYPE
        SYNTAX INTEGER
        {
               normal(1),
               alarm(2)
        }
        MAX-ACCESS read-only
        STATUS current
        DESCRIPTION
          "
          	接口LOS状态:(1:正常,2:告警)
          "
        ::= {rcftInterfaceStatEntry 8}
    rcftInterfaceCV OBJECT-TYPE
        SYNTAX INTEGER
        {
               normal(1),
               alarm(2)
        }
        MAX-ACCESS read-only
        STATUS current
        DESCRIPTION
          "
          	接口CV状态:(1:正常,2:告警)
          "
        ::= {rcftInterfaceStatEntry 9}

    rcftInterfaceAIS OBJECT-TYPE
        SYNTAX INTEGER
        {
               normal(1),
               alarm(2)
        }
        MAX-ACCESS read-only
        STATUS current
        DESCRIPTION
          "
          	接口AIS状态:(1:正常,2:告警)
          "
        ::= {rcftInterfaceStatEntry 10}

    rcftInterfaceLOF OBJECT-TYPE
        SYNTAX INTEGER
        {
               normal(1),
               alarm(2)
        }
        MAX-ACCESS read-only
        STATUS current
        DESCRIPTION
          "
          	接口LOF状态:(1:正常,2:告警)
          "
        ::= {rcftInterfaceStatEntry 11}


    rcftInterfaceCRC OBJECT-TYPE
        SYNTAX INTEGER
        {
               normal(1),
               alarm(2)
        }
        MAX-ACCESS read-only
        STATUS current
        DESCRIPTION
          "
          	接口CRC状态:(1:正常,2:告警)
          "
        ::= {rcftInterfaceStatEntry 12}

    rcftInterfaceE5 OBJECT-TYPE
        SYNTAX INTEGER
        {
               normal(1),
               alarm(2)
        }
        MAX-ACCESS read-only
        STATUS current
        DESCRIPTION
          "
          	接口误码E5状态:(1:正常,2:告警)
          "
        ::= {rcftInterfaceStatEntry 13}

    rcftInterfaceRLOS OBJECT-TYPE
        SYNTAX INTEGER
        {
               normal(1),
               alarm(2)
        }
        MAX-ACCESS read-only
        STATUS current
        DESCRIPTION
          "
          	远端接口LOS状态:(1:正常,2:告警)
          "
        ::= {rcftInterfaceStatEntry 14}
    rcftInterfaceRCV OBJECT-TYPE
        SYNTAX INTEGER
        {
               normal(1),
               alarm(2)
        }
        MAX-ACCESS read-only
        STATUS current
        DESCRIPTION
          "
          	远端接口CV状态:(1:正常,2:告警)
          "
        ::= {rcftInterfaceStatEntry 15}

    rcftInterfaceRAIS OBJECT-TYPE
        SYNTAX INTEGER
        {
               normal(1),
               alarm(2)
        }
        MAX-ACCESS read-only
        STATUS current
        DESCRIPTION
          "
          	远端接口AIS状态:(1:正常,2:告警)
          "
        ::= {rcftInterfaceStatEntry 16}

    rcftInterfaceRLOF OBJECT-TYPE
        SYNTAX INTEGER
        {
               normal(1),
               alarm(2)
        }
        MAX-ACCESS read-only
        STATUS current
        DESCRIPTION
          "
          	远端接口LOF状态:(1:正常,2:告警)
          "
        ::= {rcftInterfaceStatEntry 17}

    rcftInterfaceRCRC OBJECT-TYPE
        SYNTAX INTEGER
        {
               normal(1),
               alarm(2)
        }
        MAX-ACCESS read-only
        STATUS current
        DESCRIPTION
          "
          	远端接口LOF状态:(1:正常,2:告警)
          "
        ::= {rcftInterfaceStatEntry 18}

    rcftInterfaceUnUsed OBJECT-TYPE
        SYNTAX INTEGER
        {
               unused(1),
               used(2)
        }
        MAX-ACCESS read-write
        STATUS current
        DESCRIPTION
          "
          	接口是否被使用:(1:没有,2:有)
          "
        ::= {rcftInterfaceStatEntry 19}

    rcftInterfaceStat OBJECT-TYPE
        SYNTAX INTEGER
        {
            open(1),
            close(2)
        }
        MAX-ACCESS read-write
        STATUS current
        DESCRIPTION
          "
          	接口状态:(1:打开,2:关闭)
          "
        ::= {rcftInterfaceStatEntry 20}

     rcftInterfaceLink OBJECT-TYPE
        SYNTAX INTEGER
        {
            link(1),
            unlink(2)
        }
        MAX-ACCESS read-only
        STATUS current
        DESCRIPTION
          "
          	接口LINK(1:LINK, 2:UNLINK)
          "
        ::= {rcftInterfaceStatEntry 21}

    rcftInterfaceAutoNegotiation OBJECT-TYPE
        SYNTAX INTEGER
        {
            auto(1),
            manul(2)
        }
        MAX-ACCESS read-write
        STATUS current
        DESCRIPTION
          "
          	接口速率协商状态(1:自协商,2:手动)
          "
        ::= {rcftInterfaceStatEntry 22}

    rcftInterfaceDuplex OBJECT-TYPE
        SYNTAX INTEGER
        {
            full-duplex(1),
            half-duplex(2),
            auto(3)
        }
        MAX-ACCESS read-write
        STATUS current
        DESCRIPTION
          "
          	接口双工状态(1:全双工,2:半双工,3:自动)
          "
        ::= {rcftInterfaceStatEntry 23}

    rcftInterfaceSpeed OBJECT-TYPE
        SYNTAX INTEGER
        {
            rcft10Mbps(1),
            rcft100Mbps(2),
            rcft1000Mbps(3),
            rcft10Gbps(4),
            other(16)
        }
        MAX-ACCESS read-write
        STATUS current
        DESCRIPTION
          "
        	接口速率(1:10Mbps,2:100Mbps,3:1000Mbps,4:10Gbps,16:其他)
          "
        ::= {rcftInterfaceStatEntry 24}

    rcftInterfaceTag OBJECT-TYPE
        SYNTAX INTEGER
        {
            tag(1),
            untag(2)
        }
        MAX-ACCESS read-write
        STATUS current
        DESCRIPTION
          "
          	接口工作方式(1:TAG,2:UNTAG)
          "
        ::= {rcftInterfaceStatEntry 25}

    rcftInterfaceRecvRestrictSpeed OBJECT-TYPE
      SYNTAX INTEGER
        MAX-ACCESS read-write
        STATUS current
        DESCRIPTION
          "
          	接口接收限定速率:(n * value;n = 0,1,2....2^12. value = 32kb/s).
          "
        ::= {rcftInterfaceStatEntry 26}

    rcftInterfaceSendRestrictSpeed OBJECT-TYPE
      SYNTAX INTEGER
        MAX-ACCESS read-write
        STATUS current
        DESCRIPTION
          "
          	接口发送限定速率:(n * value;n = 0,1,2....2^12. value = 32kb/s).
          "
        ::= {rcftInterfaceStatEntry 27}

    rcftInterfaceRTag OBJECT-TYPE
        SYNTAX INTEGER
        {
            tag(1),
            untag(2)
        }
        MAX-ACCESS read-write
        STATUS current
        DESCRIPTION
        "
         	远端模块电口输出帧tag标志
        "
        ::= {rcftInterfaceStatEntry 28}

	rcftInterfaceRRecvFluxCount OBJECT-TYPE
		SYNTAX INTEGER
		MAX-ACCESS read-only
		STATUS current
		DESCRIPTION
		"
			远端模块接收方向的统计流量
		"
        ::= {rcftInterfaceStatEntry 29}

	rcftInterfaceRSendFluxCount OBJECT-TYPE
		SYNTAX INTEGER
		MAX-ACCESS read-only
		STATUS current
		DESCRIPTION
		"
			远端模块发送方向的统计流量
		"
        ::= {rcftInterfaceStatEntry 30}

 	rcftInterfaceRRecvFluxTimer OBJECT-TYPE
 		SYNTAX Counter32
 		MAX-ACCESS read-only
 		STATUS current
 		DESCRIPTION
 		"
 			接口接收流量的统计时间
 		"
        ::= {rcftInterfaceStatEntry 31}

 	rcftInterfaceRSendFluxTimer OBJECT-TYPE
 		SYNTAX Counter32
 		MAX-ACCESS read-only
 		STATUS current
 		DESCRIPTION
 		"
 			接口发送流量的统计时间
 		"
        ::= {rcftInterfaceStatEntry 32}

     rcftInterfaceRpriority   OBJECT-TYPE
     	SYNTAX INTEGER
     	{
     	    high(1),
     	    low(2)
     	}
     	MAX-ACCESS read-write
     	STATUS current
     	DESCRIPTION
     	"
     	  接口的优先级
     	"
     	::= {rcftInterfaceStatEntry 33}

     rcftInterfaceRMDIXAuto OBJECT-TYPE
     	SYNTAX INTEGER
     	{
     		enable(1),
     		disable(2)
     	}
    	MAX-ACCESS read-write
     	STATUS current
     	DESCRIPTION
     	"
     	  接口的交叉自适应功能使能
     	"
     	::= {rcftInterfaceStatEntry 34}

     rcftInterfaceRRecvRestrictSpeed OBJECT-TYPE
     	SYNTAX INTEGER
     	MAX-ACCESS read-write
     	STATUS current
     	DESCRIPTION
     	"
     		接口的接收带宽
     	"
     	::= {rcftInterfaceStatEntry 35}

     rcftInterfaceRFlowCtrl	OBJECT-TYPE
     	SYNTAX INTEGER
     	{
     		enable(1),
     		disable(2)
     	}
     	MAX-ACCESS	 read-write
     	STATUS	current
     	DESCRIPTION
     	"
     	   远端设备接口的流控功能
     	"
     	::= {rcftInterfaceStatEntry 36}

    rcftInterfaceRAudioType OBJECT-TYPE
        SYNTAX INTEGER
        {
          	magnet(1),
          	fxo(2),
          	fxs(3),
          	reserved(4)
        }
        MAX-ACCESS read-only
        STATUS current
        DESCRIPTION
        "
         -- 语音模块类型:(1:磁石模块,2:FXO语音模块,3:FXS语音模块)
        "
        ::= {rcftInterfaceStatEntry 37}

     rcftInterfaceRAudioTimeSlots  OBJECT-TYPE
     	SYNTAX Unsigned32
     	MAX-ACCESS read-write
		STATUS current
		DESCRIPTION
		"
		-- 占用时隙信息,其中0时隙不能占用,
 		-- 在成帧模式为PCM30时,不能占用16时隙
		"
        ::= {rcftInterfaceStatEntry 38}

    rcftInterfaceRAudioInSignalingSymbol OBJECT-TYPE
          SYNTAX INTEGER
          {
            originalSignaling(1),
            reverseSignaling(2)
          }
          MAX-ACCESS read-write
          STATUS current
          DESCRIPTION
          "
          -- 进向信令模式:(1:原信令,2:反信令)
          "
          ::= {rcftInterfaceStatEntry 39}

     rcftInterfaceRAudioOutSignalingSymbol OBJECT-TYPE
          SYNTAX INTEGER
          {
            originalSignaling(1),
            reverseSignaling(2)
          }
          MAX-ACCESS read-write
          STATUS current
          DESCRIPTION
          "
          -- 出向信令模式:(1:原信令,2:反信令)
          "
          ::= {rcftInterfaceStatEntry 40}

    rcftInterfaceRAudioInSignalingType   OBJECT-TYPE
          SYNTAX INTEGER
          {
          	aBit(1),
          	bBit(2)
          }
          MAX-ACCESS read-write
          STATUS current
          DESCRIPTION
          "
          -- 进向信令占用位置,1:占用a比特,2:占用b比特
          "
         ::= {rcftInterfaceStatEntry 41}

    rcftInterfaceRAudioOutSignalingType   OBJECT-TYPE
          SYNTAX INTEGER
          {
          	aBit(1),
          	bBit(2)
          }
          MAX-ACCESS read-write
          STATUS current
          DESCRIPTION
          "
          -- 出向信令占用位置,1:占用a比特,2:占用b比特
          "
         ::= {rcftInterfaceStatEntry 42}

    rcftInterfaceRAudioInSignalingStatus  OBJECT-TYPE
          SYNTAX INTEGER
          {
          	idle(1),
          	occupied(2)
          }
          MAX-ACCESS read-only
          STATUS current
          DESCRIPTION
          "
          -- 进向信令的状态,(1:空闲,2:占用)
          "
         ::= {rcftInterfaceStatEntry 43}


    rcftInterfaceRAudioOutSignalingStatus  OBJECT-TYPE
          SYNTAX INTEGER
          {
          	idle(1),
          	occupied(2)
          }
          MAX-ACCESS read-only
          STATUS current
          DESCRIPTION
          "
          -- 出向信令的状态,(1:空闲,2:占用)
          "
         ::= {rcftInterfaceStatEntry 44}

      rcftInterfaceRAudioUseEnable	OBJECT-TYPE
           SYNTAX INTEGER
          {
          	enable(1),
          	disable(2)
          }
          MAX-ACCESS read-write
          STATUS current
          DESCRIPTION
          "
          -- 语音模块是否被使用:(1:使用 ,2:禁止)
          "
          ::= {rcftInterfaceStatEntry 45}


    rcftInterfaceWANToLANFPEnWANDownLANPortStatus OBJECT-TYPE
    		SYNTAX INTEGER
    		{
				linkup (1),
				linkdown (2)
    		}
    		MAX-ACCESS	read-only
    		STATUS 		current
    		DESCRIPTION
    		"
    			本端模块线路侧到客户侧故障转移功能使能且线路侧端口linkdown时客户侧端口的状态
    			1:linkup
    			2:linkdown
    		"
    		::= {rcftInterfaceStatEntry 46}

     rcftInterfaceWANTOLANFPEnRemoteLANDownLANPortStatus	OBJECT-TYPE
    		SYNTAX INTEGER
    		{
				linkup (1),
				linkdown (2)
    		}
    		MAX-ACCESS	read-only
    		STATUS 		current
    		DESCRIPTION
    		"
    			本端模块线路侧到客户侧故障转移功能使能且远端客户侧端口linkdown时本地客户侧的端口的状态
    			1:linkup
    			2:linkdown
    		"
    		::= {rcftInterfaceStatEntry 47}

    rcftInterfaceRecvFluxCount   OBJECT-TYPE
    	SYNTAX INTEGER
    	MAX-ACCESS read-only
    	STATUS	   current
    	DESCRIPTION
    	"
    		本端模块端口接收字节数
    	"
    	::= {rcftInterfaceStatEntry 48}

    rcftInterfaceSendFluxCount   OBJECT-TYPE
    	SYNTAX INTEGER
    	MAX-ACCESS read-only
    	STATUS	   current
    	DESCRIPTION
    	"
    		本端模块端口发送字节数
    	"
    	::= {rcftInterfaceStatEntry 49}


    rcftInterfaceRecvFluxPacket	OBJECT-TYPE
    	SYNTAX INTEGER
    	MAX-ACCESS	read-only
    	STATUS current
    	DESCRIPTION
    	"
    		本端模块端口接收帧数
    	"
    	::= {rcftInterfaceStatEntry 50}

     rcftInterfaceSendFluxPacket	OBJECT-TYPE
    	SYNTAX INTEGER
    	MAX-ACCESS	read-only
    	STATUS current
    	DESCRIPTION
    	"
    		本端模块端口发送帧数
    	"
    	::= {rcftInterfaceStatEntry 51}

    rcftInterfaceRecvErrFluxPacket	OBJECT-TYPE
    	SYNTAX INTEGER
    	MAX-ACCESS	read-only
    	STATUS current
    	DESCRIPTION
    	"
    		本端模块端口接收错误帧数
    	"
    	::= {rcftInterfaceStatEntry 52}

     rcftInterfaceSendErrFluxPacket	OBJECT-TYPE
    	SYNTAX INTEGER
    	MAX-ACCESS	read-only
    	STATUS current
    	DESCRIPTION
    	"
    		本端模块端口发送失败帧数
    	"
    	::= {rcftInterfaceStatEntry 53}

	rcftInterfaceRecvFluxTimer OBJECT-TYPE
 		SYNTAX Counter32
 		MAX-ACCESS read-only
 		STATUS current
 		DESCRIPTION
 		"
 			本端模块接口接收流量的统计时间
 		"
        ::= {rcftInterfaceStatEntry 54}

 	rcftInterfaceSendFluxTimer OBJECT-TYPE
 		SYNTAX Counter32
 		MAX-ACCESS read-only
 		STATUS current
 		DESCRIPTION
 		"
 			本端模块接口发送流量的统计时间
 		"
        ::= {rcftInterfaceStatEntry 55}


     rcftInterfaceRSendRestrictSpeed OBJECT-TYPE
     	SYNTAX INTEGER
     	MAX-ACCESS read-write
     	STATUS current
     	DESCRIPTION
     	"
     		接口的发送带宽  n * value;n = 0,1,2....2^12. value = 32kb/s
     	"
     	::= {rcftInterfaceStatEntry 56}


    rcftInterfaceRWANToLANFPEnWANDownLANPortStatus OBJECT-TYPE
    		SYNTAX INTEGER
    		{
				open (1),
				close (2)
    		}
    		MAX-ACCESS	read-only
    		STATUS 		current
    		DESCRIPTION
    		"
    			远端模块线路侧到客户侧故障转移功能使能且线路侧端口linkdown时远端客户侧端口的状态
    			1:linkup
    			2:linkdown
    		"
    		::= {rcftInterfaceStatEntry 57}

     rcftInterfaceRWANTOLANFPEnRemoteLANDownLANPortStatus	OBJECT-TYPE
    		SYNTAX INTEGER
    		{
				open (1),
				close (2)
    		}
    		MAX-ACCESS	read-only
    		STATUS 		current
    		DESCRIPTION
    		"
    			线路侧到客户侧故障转移功能使能且本端客户侧端口linkdown时远端客户侧端口的状态
    			1:linkup
    			2:linkdown
    		"
    		::= {rcftInterfaceStatEntry 58}

     rcftInterfaceRRecvFluxPacket	OBJECT-TYPE
    	SYNTAX INTEGER
    	MAX-ACCESS	read-only
    	STATUS current
    	DESCRIPTION
    	"
    		远端模块端口接收帧数
    	"
    	::= {rcftInterfaceStatEntry 59}

     rcftInterfaceRSendFluxPacket	OBJECT-TYPE
    	SYNTAX INTEGER
    	MAX-ACCESS	read-only
    	STATUS current
    	DESCRIPTION
    	"
    		远端模块端口发送帧数
    	"
    	::= {rcftInterfaceStatEntry 60}

    rcftInterfaceRRecvErrFluxPacket	OBJECT-TYPE
    	SYNTAX INTEGER
    	MAX-ACCESS	read-only
    	STATUS current
    	DESCRIPTION
    	"
    		远端模块端口接收错误帧数
    	"
    	::= {rcftInterfaceStatEntry 61}

     rcftInterfaceRSendErrFluxPacket	OBJECT-TYPE
    	SYNTAX INTEGER
    	MAX-ACCESS	read-only
    	STATUS current
    	DESCRIPTION
    	"
    		远端模块端口发送失败帧数
    	"
    	::= {rcftInterfaceStatEntry 62}

    rcftInterfaceFoundLink OBJECT-TYPE
        SYNTAX INTEGER
        {
               success(1),
               failForDelay(2),
               failForOtherReason(100)
        }
        MAX-ACCESS read-only
        STATUS current
        DESCRIPTION
          "
          	局端接口是否建链成功:
          	1:成功；
          	2：失败，并且失败的原因是延迟造成的；
          	100：失败，并且是其它原因造成的；
          "
        ::= {rcftInterfaceStatEntry 63}

    rcftInterfaceBERT OBJECT-TYPE
        SYNTAX INTEGER
        {
            enable(1),
            disable(2)
        }
        MAX-ACCESS read-only
        STATUS current
        DESCRIPTION
          "
          	误码仪的状态:(1:使能,2:不使能)
          "
        ::= {rcftInterfaceStatEntry 64}

    rcftInterfaceCLKMode OBJECT-TYPE
        SYNTAX INTEGER
        {
	       secondary(1),
	   	   v35terminal(2),
           master(3),
           reserved(4)
      }
        MAX-ACCESS read-write
        STATUS current
        DESCRIPTION
          "
              本端模块的工作时钟方式状态:(1:从时钟,2:V35终端时钟,3:主时钟).
          "
        ::= {rcftInterfaceStatEntry 65}

    rcftInterfaceCRCStatus OBJECT-TYPE
        SYNTAX INTEGER
        {
	   	   enable(1),
           disable(2)
        }
        MAX-ACCESS read-only
        STATUS current
        DESCRIPTION
          "
          	局端CRC的状态:(1:处于CRC的状态,2:不处于CRC的状态).
          "
        ::={rcftInterfaceStatEntry 66}

    rcftInterfaceCRCEnable OBJECT-TYPE
        SYNTAX INTEGER
        {
	   	   enable(1),
           disable(2)
        }
        MAX-ACCESS read-write
        STATUS current
        DESCRIPTION
          "
          	局端CRC自适应状态:(1:enable,2:disable).
          "
        ::={rcftInterfaceStatEntry 67}

    rcftInterfaceLocalLoopEn OBJECT-TYPE
        SYNTAX INTEGER
        {
            enable(1),
            disable(2)
        }
        MAX-ACCESS read-only
        STATUS current
        DESCRIPTION
          "
          	局端E1口工作在局端环回:(1:使能,2:不使能)
          "
        ::= {rcftInterfaceStatEntry 68}

    rcftInterfaceRemoteLoopEn OBJECT-TYPE
        SYNTAX INTEGER
        {
            enable(1),
            disable(2)
        }
        MAX-ACCESS read-only
        STATUS current
        DESCRIPTION
          "
          	局端E1工作在远端环回:(1:使能,2:不使能)
          "
        ::= {rcftInterfaceStatEntry 69}

    rcftInterfaceTransErrorCode OBJECT-TYPE
        SYNTAX INTEGER
    	{
    	   less10E-6(1),
    	   more10E-6(2),
    	   more10E-3(3)
    	}
    	MAX-ACCESS read-only
    	STATUS current
    	DESCRIPTION
    	   "
    	  	本端模块传输误码率(1:小于10E-6,2:大于10E-6,小于10E-3,3:大于10E-3).
    	   "
        ::={rcftInterfaceStatEntry 70}

    rcftInterfaceE1Location OBJECT-TYPE
        SYNTAX INTEGER
    	{
    	   e1-1(1),
    	   e1-2(2),
    	   e1-3(3),
    	   e1-4(4),
    	   e1-5(5),
    	   e1-6(6),
    	   e1-7(7),
    	   e1-8(8),
    	   unknown(100)
    	}
    	MAX-ACCESS read-write
    	STATUS current
    	DESCRIPTION
    	   "
    	  	局端对应的远端是第几路E1口(1:E1-1,2:E1-2,3:E1-3,4:E1-4).
    	   "
        ::={rcftInterfaceStatEntry 71}

    rcftInterfaceE1ESCnt OBJECT-TYPE
    	SYNTAX INTEGER
    	MAX-ACCESS read-only
    	STATUS current
    	DESCRIPTION
    	"
    		局端设备E1误码秒统计计数
    	"
         ::={rcftInterfaceStatEntry 72}

    rcftInterfaceE1SESCnt OBJECT-TYPE
    	SYNTAX INTEGER
    	MAX-ACCESS read-only
    	STATUS current
    	DESCRIPTION
    	"
    		局端设备E1严重误码秒统计计数
    	"
   	    ::={rcftInterfaceStatEntry 73}

    rcftInterfaceE1TimeSlot OBJECT-TYPE
       	SYNTAX Unsigned32
       	MAX-ACCESS read-write
       	STATUS current
       	DESCRIPTION
       	"
       	   局端E1时隙
       	   0-30位分别表示E1的31个时隙,置1表示该时隙使能,0表示该时隙禁止
       	"
       	::={rcftInterfaceStatEntry 74}

    rcftInterfaceE1Transparent OBJECT-TYPE
        SYNTAX INTEGER
        {
              transparent(1),
    	      pcm(2)
        }
        MAX-ACCESS read-write
        STATUS current
        DESCRIPTION
          "
          	局端E1传送方式:(1:透明方式,2:成帧方式).
          "
        ::={rcftInterfaceStatEntry 75}

    rcftStmStatTable OBJECT-TYPE
        SYNTAX SEQUENCE OF RcftStmStatEntry
        MAX-ACCESS not-accessible
        STATUS current
        DESCRIPTION
          " The table holding information related to the stm card status."
        ::= {rcftSlotStat 3}

    rcftStmStatEntry OBJECT-TYPE
        SYNTAX RcftStmStatEntry
        MAX-ACCESS not-accessible
        STATUS current
        DESCRIPTION
          "  "
        INDEX { rcftChassisIndex, rcftSlotIndex }
        ::= {rcftStmStatTable 1}

    RcftStmStatEntry ::= SEQUENCE {

            rcftStmAdminStatus
                INTEGER,
            rcftStmFiberPort
           	INTEGER,
            rcftStmFiberRxPllUnlck
            	INTEGER,
            rcftStmFiberTxClkLos
            	INTEGER,
            rcftStmFiberAnalogLos
            	INTEGER,
            rcftStmFiberDigitalLos
            	INTEGER,
            rcftStmFiberSyncLos
           	INTEGER,
            rcftStmBncPort
           	INTEGER,
            rcftStmBncRxPllUnlck
            	INTEGER,
            rcftStmBncTxClkLos
            	INTEGER,
            rcftStmBncAnalogLos
            	INTEGER,
            rcftStmBncDigitalLos
            	INTEGER,
            rcftStmBncSyncLos
           		INTEGER
}

    rcftStmAdminStatus OBJECT-TYPE
        SYNTAX INTEGER
        {
          fiberPortLoopbackTestMode1Enable(1),
          fiberPortLoopbackTestDisable(2),
          fiberPortLoopbackTestMode2Enable(3),
          bncPortLoopbackTestMode1Enable(4),
	      bncPortLoopbackTestDisable(5),
          bncPortLoopbackTestMode2Enable(6)
        }
        MAX-ACCESS read-write
        STATUS current
        DESCRIPTION
          "
         	光电转换器的管理命令:(1:光口环回测试模式1使能;2:光口环回测试禁止;3:光口环回测试模式2使能;
          	4:同轴电缆接口环回测试模式1使能;5:同轴电缆接口环回测试禁止;6:同轴电缆接口环回测试模式2使能;)
          "
        ::= {rcftStmStatEntry 1}

    rcftStmFiberPort OBJECT-TYPE
        SYNTAX INTEGER
        {
               open(1),
               close(2)
        }
        MAX-ACCESS read-write
        STATUS current
        DESCRIPTION
          "
          	光口状态:(1:打开;2:关闭;)
          "
        ::= {rcftStmStatEntry 2}

    rcftStmFiberRxPllUnlck OBJECT-TYPE
        SYNTAX INTEGER
        {
               normal(1),
               alarm(2)
        }
        MAX-ACCESS read-only
        STATUS current
        DESCRIPTION
          "
          	光口接收锁相环状态:(1:正常;2:告警;)
          "
        ::= {rcftStmStatEntry 3}

    rcftStmFiberTxClkLos OBJECT-TYPE
        SYNTAX INTEGER
        {
               normal(1),
               alarm(2)
        }
        MAX-ACCESS read-only
        STATUS current
        DESCRIPTION
          "
          	光口发送时钟状态状态:(1:正常;2:告警;)
          "
        ::= {rcftStmStatEntry 4}

    rcftStmFiberAnalogLos OBJECT-TYPE
        SYNTAX INTEGER
        {
               normal(1),
               alarm(2)
        }
        MAX-ACCESS read-only
        STATUS current
        DESCRIPTION
          "
          	光口模拟信号状态:(1:正常;2:告警;)
          "
        ::= {rcftStmStatEntry 5}

    rcftStmFiberDigitalLos OBJECT-TYPE
        SYNTAX INTEGER
        {
               normal(1),
               alarm(2)
        }
        MAX-ACCESS read-only
        STATUS current
        DESCRIPTION
          "
          	光口数字信号状态:(1:正常;2:告警;)
          "
        ::= {rcftStmStatEntry 6}

    rcftStmFiberSyncLos OBJECT-TYPE
        SYNTAX INTEGER
        {
               normal(1),
               alarm(2)
        }
        MAX-ACCESS read-only
        STATUS current
        DESCRIPTION
          "
          	光口帧失步状态:(1:正常;2:告警;)
          "
        ::= {rcftStmStatEntry 7}

    rcftStmBncPort OBJECT-TYPE
        SYNTAX INTEGER
        {
               open(1),
               close(2)
        }
        MAX-ACCESS read-write
        STATUS current
        DESCRIPTION
          "
          	同轴电缆接口状态:(1:打开;2:关闭;)
          "
        ::= {rcftStmStatEntry 8}

    rcftStmBncRxPllUnlck OBJECT-TYPE
        SYNTAX INTEGER
        {
               normal(1),
               alarm(2)
        }
        MAX-ACCESS read-only
        STATUS current
        DESCRIPTION
          "
          	同轴电缆接口接收锁相环状态:(1:正常;2:告警;)
          "
        ::= {rcftStmStatEntry 9}

    rcftStmBncTxClkLos OBJECT-TYPE
        SYNTAX INTEGER
        {
               normal(1),
               alarm(2)
        }
        MAX-ACCESS read-only
        STATUS current
        DESCRIPTION
          "
           	同轴电缆接口发送时钟状态:(1:正常;2:告警;)
          "
        ::= {rcftStmStatEntry 10}

    rcftStmBncAnalogLos OBJECT-TYPE
        SYNTAX INTEGER
        {
               normal(1),
               alarm(2)
        }
        MAX-ACCESS read-only
        STATUS current
        DESCRIPTION
          "
          	同轴电缆接口模拟信号状态:(1:正常;2:告警;)
          "
        ::= {rcftStmStatEntry 11}

    rcftStmBncDigitalLos OBJECT-TYPE
        SYNTAX INTEGER
        {
               normal(1),
               alarm(2)
        }
        MAX-ACCESS read-only
        STATUS current
        DESCRIPTION
          "
           	同轴电缆接口数字信号状态:(1:正常;2:告警;)
          "
        ::= {rcftStmStatEntry 12}

    rcftStmBncSyncLos OBJECT-TYPE
        SYNTAX INTEGER
       {
             normal(1),
             alarm(2)
       }
        MAX-ACCESS read-only
         STATUS current
       DESCRIPTION
        "
         	同轴电缆接口帧失步状态:(1:正常;2:告警;)

        "
       ::= {rcftStmStatEntry 13}

    rcftConfigFlagTable OBJECT-TYPE
        SYNTAX SEQUENCE OF RcftConfigFlagEntry
        MAX-ACCESS not-accessible
        STATUS current
        DESCRIPTION
          " "
        ::= {rcftSlotStat 11}

    rcftConfigFlagEntry OBJECT-TYPE
        SYNTAX RcftConfigFlagEntry
        MAX-ACCESS not-accessible
        STATUS current
        DESCRIPTION
          "  "
        INDEX { rcftChassisIndex, rcftSlotIndex }
        ::= {rcftConfigFlagTable 1}

    RcftConfigFlagEntry ::= SEQUENCE {
		 rcftLocalDeviceConfigFinishFlag
		 INTEGER
		}

    rcftLocalDeviceConfigFinishFlag OBJECT-TYPE
        SYNTAX INTEGER
        MAX-ACCESS read-write
        STATUS current
        DESCRIPTION
        "
			对局端设备配置结束标志。
		    该对象作为一次网管配置的结束标志.在进行配置操作时网管一次可
          以绑定若干个对象,但SNMP VB邦定的最后一个VB必须为rcftLocalDeviceConfigFlag,
          且置1,以表明本次配置结束.同样在发送命令字时在绑定rcftSlotOrder或
          rcftRSlotOrder的同时要绑定rcftLocalDeviceConfigFlag,以表明本次命令结束.
          Agent通过判断这个标志才能进行配置或命令操作.
            该对象与rcftSlotRowStatus的区别是新设备都用该对象作为结束标志。
            具体哪些对象使用该对象，在配置说明文档中会给出说明。
        "
       ::= {rcftConfigFlagEntry 1}
    rcftSlotConfStatTable OBJECT-TYPE
        SYNTAX SEQUENCE OF RcftSlotConfStatEntry
        MAX-ACCESS not-accessible
        STATUS current
        DESCRIPTION
        "
          The table holding information related to the card status.
          注:表中的对象是所有板卡状态对象的全集,针对某一类型的板卡,
          只有与其相关的状态对象有意义,而其它的对象值没有意义,被清0.
        "
        ::= {rcftSlotStat 12}

    rcftSlotConfStatEntry OBJECT-TYPE
        SYNTAX RcftSlotConfStatEntry
        MAX-ACCESS not-accessible
        STATUS current
        DESCRIPTION
        "
          The card config information entry.
        "
        INDEX { rcftChassisIndex, rcftSlotIndex }
        ::= {rcftSlotConfStatTable 1}

    RcftSlotConfStatEntry ::= SEQUENCE {
        rcftSlotConfEDuplex
            INTEGER,
        rcftSlotConfESpeed
            INTEGER,
        rcftRSlotConfEDuplex
        	INTEGER,
        rcftRSlotConfESpeed
            INTEGER,
        rcftConfTxWorkStatus
            INTEGER
        }

    rcftSlotConfEDuplex OBJECT-TYPE
        SYNTAX INTEGER
        {
            full-duplex(1),
            half-duplex(2),
            auto(3)
         }
        MAX-ACCESS read-write
        STATUS current
        DESCRIPTION
          "
          本模块电口双工模式配置信息(1:全双工,2:半双工,3:自动).
          The duplex mode of the electronic port for configration.
          1:full duplex
          2:half duplex
          3:auto
          "
        ::= {rcftSlotConfStatEntry 1}

    rcftSlotConfESpeed OBJECT-TYPE
        SYNTAX INTEGER
        {
            rcft10Mbps(1),
            rcft100Mbps(2),
            rcft1000Mbps(3),
            rcft10Gbps(4),
            other(16)
        }
        MAX-ACCESS read-write
        STATUS current
        DESCRIPTION
          "
            电口的速率配置信息.
            The speed of the electronic port for configration.
            1.10Mbps
            2.100Mbps
            3.1000Mbps
            4.10Gbps
            5.other
          "
        ::= {rcftSlotConfStatEntry 2}

    rcftRSlotConfEDuplex OBJECT-TYPE
        SYNTAX INTEGER
        {
            full-duplex(1),
            half-duplex(2),
            auto(3)
         }
        MAX-ACCESS read-write
        STATUS current
        DESCRIPTION
          "
          一级远端电口双工模式配置信息(1:全双工,2:半双工,3:自动).
          The duplex mode of the electronic port for configration.
          1:full duplex
          2:half duplex
          3:auto
          "
        ::= {rcftSlotConfStatEntry 3}


    rcftRSlotConfESpeed OBJECT-TYPE
        SYNTAX INTEGER
        {
            rcft10Mbps(1),
            rcft100Mbps(2),
            rcft1000Mbps(3),
            rcft10Gbps(4),
            other(16)
        }
        MAX-ACCESS read-write
        STATUS current
        DESCRIPTION
         "
       	   远端模块电口的工作速率配置信息1:10Mbps,2:100Mbps,3:1000Mbps,4:10Gbps,16:其他).
       	   The speed of the electronic port in the remote module for configration.
            1:10Mbps
            2.100Mbps
            3.1000Mbps
            4.10Gbps
            5.other
         "
        ::= {rcftSlotConfStatEntry 4}

    rcftConfTxWorkStatus OBJECT-TYPE
      SYNTAX INTEGER
        MAX-ACCESS read-write
        STATUS current
        DESCRIPTION
          "
          	模块的本端与远端以太网口的工作状态配置信息.

       注:在对该对象进行配置操作时,在绑定该对象的同时,需要绑定针对某一槽位的板卡类型
       rcftSlotConfCardType,如果是对本端模块进行配置操作,需要本端的板卡类型赋给rcftSlotConfCardType;
       如果是对远端模块进行配置操作,需要将远端的板卡类型赋给rcftSlotConfCardType.

          "
	::= {rcftSlotConfStatEntry 5}

    rcft5VPowerTrap NOTIFICATION-TYPE
        OBJECTS {
           rcft5vStatus
        }
        STATUS             current
        DESCRIPTION
        "
          5v电源状态异常和恢复告警.5v电源当其输出电压高于或低于5v时电源处于异常状态.
          当5v电源状态发生变化时发送该trap. 具体发送的是告警还是恢复由绑定的状态
          rcft5vStatus的值决定:1:恢复,2:告警
          5v power notification.
          When the output of the 5v-power is beyond or below 5v then the status of the power will be
          abnormal.The change of the status from normal to abnormal or from abnormal to normal will
          force the agent to send this notification to the manager.
        "
        ::= { rcftTraps 1 }

    rcft12VPowerTrap NOTIFICATION-TYPE
        OBJECTS {
           rcft12vStatus
        }
        STATUS             current
        DESCRIPTION
        "
          12v电源状态异常和恢复告警.12v电源当其输出电压高于或低于12v时电源处于异常状态.
          当12v电源状态发生变化时(从正常->异常,从异常->正常)发送该trap.具体发送的是
          告警还是恢复由绑定的状态rcft12vStatus的值决定:1:恢复,2:告警
          12v power notification.
          When the output of the 12v-power is beyond or below 12v then the status of the power will be
          abnormal.The change of the status from normal to abnormal or from abnormal to normal will
          force the agent to send this notification to the manager.

        "
        ::= { rcftTraps 2 }

    rcftFanTrap NOTIFICATION-TYPE
        OBJECTS {
           rcftFanStatus
        }
        STATUS             current
        DESCRIPTION
        "
          风扇异常告警和恢复.当风扇状态发生变化时发送该trap,具体是告警
          还是恢复由绑定的状态rcftFanStatus的值决定:
          1:恢复,2:告警
          This notification will be sent to the manager when fan status is
          changing from normanl to abnormal or from   abnormal to normal.
        "
        ::= { rcftTraps 3 }

    rcftTmptTrap NOTIFICATION-TYPE
        OBJECTS {
           rcftChassisTmpt
        }
        STATUS             current
        DESCRIPTION
        "
          机箱温度告警和恢复. 当机箱温度超过阀值rcftSysTmptAlarmThreshold时
          发送温度异常告警,当温度又恢复到正常水平时发送温度恢复告警.
          Chassis temperature trap.
          This trap will be sent when the chassis temperature becomes beyond or below to
          the value of the rcftSysTmptAlarmThreshold .
        "
        ::= { rcftTraps 4 }

    rcftChassisTrap NOTIFICATION-TYPE
        OBJECTS {
           rcftChassisExist
        }
        STATUS             current
        DESCRIPTION
        "
           机箱丢失告警和恢复.当某一机箱在位状态发生变化时(从存在到丢失,从丢失到恢复在位)发送该告警,
           具体发送的是告警还是恢复由绑定的状态rcftChassisExist的值决定:
           1:恢复,2:告警
           When the status of the chassis with index of rcftChassisIndex is changing from exist
           to lost or from lost to exist this trap will be sent to the manager.
        "
        ::= { rcftTraps 5 }


    rcftELinkTrap NOTIFICATION-TYPE
        OBJECTS {
           rcftSlotELink
        }
        STATUS             current
        DESCRIPTION
        "
           局端模块电口link状态变化告警及恢复.
           当电口link状态由up变down时发送告警,由down变up时发送告警恢复.
           The change of the link status of the eth port in the local module
           will generate this trap.
        "
        ::= { rcftTraps 6 }

    rcftRELinkTrap NOTIFICATION-TYPE
        OBJECTS {
           rcftRSlotELink
        }
        STATUS             current
        DESCRIPTION
        "
          远端模块电口link状态变化告警及恢复.
          当电口link状态由up变down时发送告警,由down变up时发送告警恢复.
          The change of the link status of the eth port in the remote module
          will generate thip trap.
        "
        ::= { rcftTraps 7 }

    rcftOLinkTrap NOTIFICATION-TYPE
        OBJECTS {
           rcftSlotOLink
        }
        STATUS             current
        DESCRIPTION
        "
          单芯光模块光口link状态变化告警及恢复.
          当光口link 状态由up变down时发送告警,由down变up时发送告警恢复.
          The change of the link status of the optical port in the local module
          will generate thip trap.

        "
        ::= { rcftTraps 8 }

    rcftORLnkTrap NOTIFICATION-TYPE
        OBJECTS {
           rcftSlotORLnk
        }
        STATUS             current
        DESCRIPTION
        "
          双芯光模块光口接收方向link状态变化告警及恢复.
          光口接收方向上当link 状态由up变down时发送告警,由down变up时发送告警恢复.
          The change of the link status of the optical port in the local module
          will generate thip trap.

        "
        ::= { rcftTraps 9 }

    rcftOTLnkTrap NOTIFICATION-TYPE
        OBJECTS {
           rcftSlotOTLnk
        }
        STATUS             current
        DESCRIPTION
        "
          光口发送方向link状态变化告警及恢复.
          光口发送方向上当link 状态由up变down时发送告警,由down变up时发送告警恢复.
        "
        ::= { rcftTraps 10 }

    rcftROLinkTrap NOTIFICATION-TYPE
        OBJECTS {
           rcftRSlotOLink
        }
        STATUS             current
        DESCRIPTION
        "
        	远端光口LINK变化.
        "
        ::= { rcftTraps 11 }

    rcftESpeedTrap NOTIFICATION-TYPE
        OBJECTS {
           rcftSlotESpeed
        }
        STATUS             current
        DESCRIPTION
        "
           局端模块电口link状态变化告警及恢复. 当电口link状态由up变down时发送告警,
           由down变up时发送告警恢复.
        "
        ::= { rcftTraps 12 }

    rcftSlotTrap NOTIFICATION-TYPE
        OBJECTS {
           rcftSlotExist
        }
        STATUS             current
        DESCRIPTION
        "
          局端板卡丢失告警及恢复. 当局端板卡由在位到丢失和由丢失到恢复在位时
          发送该trap. 具体发送的是丢失告警还是告警恢复由绑定的rcftSlotExist值决定:
          1:恢复,2:告警
        "
        ::= { rcftTraps 13 }

    rcftBackplaneLossTrap NOTIFICATION-TYPE
        OBJECTS {
            rcftChassisExist
        }
        STATUS             current
        DESCRIPTION
        "
        	背板丢失.
        "
        ::= { rcftTraps 14 }

   rcftVOLimitTrap NOTIFICATION-TYPE
       OBJECTS {
          rcftSlotVOLimit
       }
       STATUS     current
       DESCRIPTION
       "
         本端电压超上限阀值告警.

       "
       ::={ rcftTraps 15 }

   rcftVBLimitTrap NOTIFICATION-TYPE
       OBJECTS {
          rcftSlotVBLimit
       }
       STATUS     current
       DESCRIPTION
       "
       		本端电压超下限阀值告警.
       "
       ::={ rcftTraps 16 }

   rcftRVOLimitTrap NOTIFICATION-TYPE
       OBJECTS {
          rcftRSlotVOLimit
       }
       STATUS     current
       DESCRIPTION
       "
         远端模块温度过高告警及恢复:当远端模块温度超过最高门限值时发送告警,
         当恢复到门限值范围内时发送告警恢复.
       "
       ::={ rcftTraps 17 }

   rcftRVBLimitTrap NOTIFICATION-TYPE
       OBJECTS {
          rcftRSlotVBLimit
       }
       STATUS     current
       DESCRIPTION
       "
          远端模块温度过低告警及恢复:当远端模块温度低于最低门限值时发送告警,
          当恢复到门限值范围内时发送告警恢复.
       "
       ::={ rcftTraps 18 }

    rcftOSendPowerTrap NOTIFICATION-TYPE
       OBJECTS {
          rcftSlotOSendPower
       }
       STATUS     current
       DESCRIPTION
       "
       	本端发送光功率变化告警.
       "
       ::={ rcftTraps 19 }

    rcftROSendPowerTrap NOTIFICATION-TYPE
       OBJECTS {
          rcftRSlotOSendPower
       }
       STATUS     current
       DESCRIPTION
       "
         远端发送光功率变化告警.
       "
       ::={ rcftTraps 20 }

   rcftOReceSenTrap NOTIFICATION-TYPE
       OBJECTS {
           rcftSlotOReceSen
       }
       STATUS     current
       DESCRIPTION
       "
         本端接收灵敏度变化告警.
       "
       ::={ rcftTraps 21 }

   rcftROReceSenTrap NOTIFICATION-TYPE
       OBJECTS {
          rcftRSlotOReceSen
       }
       STATUS     current
       DESCRIPTION
       "
          远端接收灵敏度变化告警及恢复.当rcftRSlotOReceSen的状态值发生变化时
         发送该trap. 是告警还是恢复由绑定的对象rcftRSlotOReceSen的状态值决定:
         1: 恢复,  2:告警

       "
       ::={ rcftTraps 22 }

   rcftOLaserTrap NOTIFICATION-TYPE
       OBJECTS {
          rcftSlotOLaser
       }
       STATUS     current
       DESCRIPTION
       "
         本端激光管工作状态变化告警.
       "
       ::={ rcftTraps 23 }

   rcftROLaserTrap NOTIFICATION-TYPE
       OBJECTS {
          rcftRSlotOLaser
       }
       STATUS     current
       DESCRIPTION
       "
           远端激光管工作状态变化告警及恢复.当rcftRSlotOLaser的状态值发生变化时
         发送该trap. 是告警还是恢复由绑定的对象rcftRSlotOLaser的状态值决定:
         1: 恢复,  2:告警

       "
       ::={ rcftTraps 24 }

   rcftOSDTrap NOTIFICATION-TYPE
       OBJECTS {
          rcftSlotOSD
       }
       STATUS     current
       DESCRIPTION
       "
         本地光模块SD输出信号异常告警和恢复. 当rcftSlotOSD的状态值发生变化时
         发送该trap. 是告警还是恢复由绑定的对象rcftSlotOSD的状态值决定:
         1: 恢复,  2:告警
       "
       ::={ rcftTraps 25 }

   rcftROSDTrap NOTIFICATION-TYPE
       OBJECTS {
          rcftRSlotOSD
       }
       STATUS     current
       DESCRIPTION
       "
         远端光模块SD输出信号异常告警和恢复. 当rcftRSlotOSD的状态值发生变化时
         发送该trap. 是告警还是恢复由绑定的对象rcftRSlotOSD的状态值决定:
         1: 恢复,  2:告警
       "
       ::={ rcftTraps 26 }

   rcftRSlotChassisTmptTrap NOTIFICATION-TYPE
       OBJECTS {
          rcftRSlotChassisTmpt
       }
       STATUS  current
       DESCRIPTION
       "
           远端模块所在机箱温度告警及恢复:当远端模块所在机箱温度高于门限值时发送告警,
           当恢复到门限值范围内时发送告警恢复.
       "
       ::={ rcftTraps 27}

   rcftRSlotFault  NOTIFICATION-TYPE
       OBJECTS {
          rcftRSlotExist
       }
       STATUS  current
       DESCRIPTION
       "
         远端模块故障告警
       "
       ::={ rcftTraps 28}

   rcftSlotFault  NOTIFICATION-TYPE
       OBJECTS {
          rcftSlotExist
       }
       STATUS  current
       DESCRIPTION
       "
       模块故障告警
       "
       ::={ rcftTraps 29}

  rcftRSlotExistNotify  NOTIFICATION-TYPE
       OBJECTS {
          rcftRSlotExist
       }
       STATUS  current
       DESCRIPTION
       "

          远端板卡在位状态变化告警,当远端板卡由在位到丢失时发送告警,远端板卡由丢失到恢复在位时
          发送告警恢复.
        "
       ::={ rcftTraps 30}

  rcftSlotE1LOSTRAP NOTIFICATION-TYPE
       OBJECTS {
          rcftSlotE1LOS
       }
       STATUS  current
       DESCRIPTION
       "
       本端模块E1信号消失告警
       "
       ::={ rcftTraps 31}

  rcftSlotOLOSTRAP NOTIFICATION-TYPE
       OBJECTS {
          rcftSlotOLOS
       }
       STATUS  current
       DESCRIPTION
         "
         本端模块光信号消失告警
         "
       ::={ rcftTraps 32}

  rcftSlotOSyncLOSTRAP NOTIFICATION-TYPE
       OBJECTS {
          rcftSlotOSync
       }
       STATUS  current
       DESCRIPTION
      "
      本端模块光同步丢失告警
      "
       ::={ rcftTraps 33}

  rcftSlotOTransErrorCodeMore10E-3 NOTIFICATION-TYPE
       OBJECTS {
          rcftSlotOTransErrorCode
       }
       STATUS  current
       DESCRIPTION
        "
        本端模块光传输误码率大于10E-3告警
        "
       ::={ rcftTraps 34}

  rcftSlotOTransErrorCodeMore10E-6 NOTIFICATION-TYPE
       OBJECTS {
          rcftSlotOTransErrorCode
       }
       STATUS  current
       DESCRIPTION
     "
     本端模块光传输误码率大于10E-6告警
     "
       ::={ rcftTraps 35}

  rcftRSlotE1LOSTRAP NOTIFICATION-TYPE
       OBJECTS {
          rcftRSlotE1LOS
       }
       STATUS  current
       DESCRIPTION
        "
        远端模块E1信号消失告警
        "
       ::={ rcftTraps 36}

  rcftRSlotOLOSTRAP NOTIFICATION-TYPE
       OBJECTS {
          rcftRSlotOLOS
       }
       STATUS  current
       DESCRIPTION
       "
       远端模块光信号消失告警
       "
       ::={ rcftTraps 37}

  rcftRSlotOSyncLOSTRAP NOTIFICATION-TYPE
       OBJECTS {
          rcftRSlotOSync
       }
       STATUS  current
       DESCRIPTION
       "
       远端模块光同步丢失告警
       "
       ::={ rcftTraps 38}

  rcftRSlotOTransErrorCodeMore10E-3 NOTIFICATION-TYPE
       OBJECTS {
          rcftRSlotOTransErrorCode
       }
       STATUS  current
       DESCRIPTION
       "
       远端模块光传输误码率大于10E-3告警
       "
       ::={ rcftTraps 39}

  rcftRSlotOTransErrorCodeMore10E-6 NOTIFICATION-TYPE
       OBJECTS {
          rcftRSlotOTransErrorCode
       }
       STATUS  current
       DESCRIPTION
       "
       远端模块光传输误码率大于10E-6告警
       "
       ::={ rcftTraps 40}

  rcftSlotE1LOFTRAP NOTIFICATION-TYPE
       OBJECTS {
          rcftSlotE1LOF
       }
       STATUS  current
       DESCRIPTION
       "
       E1线路LOF告警
       "
       ::={ rcftTraps 41}

  rcftSlotE1CRCTRAP NOTIFICATION-TYPE
       OBJECTS {
          rcftSlotE1CRC
       }
       STATUS  current
       DESCRIPTION
       "
       E1线路CRC告警
       "
       ::={ rcftTraps 42}

  rcftSlotSOLinkTRAP NOTIFICATION-TYPE
        OBJECTS {
           rcftSlotOLink
        }
        STATUS  current
        DESCRIPTION
        "
           单模光口link状态变化告警及恢复. 光口link 状态由up变down时发送告警,
           由down变up时发送告警恢复.
        "
        ::= { rcftTraps 43 }

  rcftSlotMOLinkTRAP NOTIFICATION-TYPE
        OBJECTS {
           rcftSlotELink
        }
        STATUS  current
        DESCRIPTION
        "
          多模光口link状态变化告警及恢复. 多模光口link 状态由up变down时发送告警,
          由down变up时发送告警恢复.
          注:对有多模光口的板卡,其多模光口的link状态借用了rcftSlotELink.所以该
          告警绑定的是rcftSlotELink
        "
        ::= { rcftTraps 44 }

-- 以下是RC102-2F10/100M二端口以太网光纤收发器模块扩展的告警

    rcftEPort1LinkTrap NOTIFICATION-TYPE
        OBJECTS {
           rcftSlotEPort1Link
        }
        STATUS  current
        DESCRIPTION
        "
        电口1LINK变化.
        "
        ::= { rcftTraps 45 }

   rcftSlotE1AISTrap NOTIFICATION-TYPE
        OBJECTS {
           rcftSlotE1AIS
        }
        STATUS  current
        DESCRIPTION
        "
        电口AIS告警.
        "
        ::= { rcftTraps 46 }

   rcftSlotRALMTrap NOTIFICATION-TYPE
        OBJECTS {
           rcftSlotRALM
        }
        STATUS  current
        DESCRIPTION
        "
        远端模块总告警.
        "
        ::= { rcftTraps 47 }


  rcftSlotE1Port2LOSTRAP NOTIFICATION-TYPE
       OBJECTS {
          rcftSlotE1Port2LOS
       }
       STATUS  current
       DESCRIPTION
       "
       本端模块E1 2支路信号消失告警
       "
       ::={ rcftTraps 48}

  rcftRSlotE1Port2LOSTRAP NOTIFICATION-TYPE
       OBJECTS {
          rcftRSlotE1Port2LOS
       }
       STATUS  current
       DESCRIPTION
       "
       远端模块E1 2支路信号消失告警
       "
       ::={ rcftTraps 49}


  rcftRESpeedTrap NOTIFICATION-TYPE
        OBJECTS {
          rcftInterfaceRSpeed
        }
        STATUS             current
        DESCRIPTION
        "
          远端模块以太网接口速率变化报警及恢复:当速率由100M变成10M时产生告警,
          当速率由10M变成100M时发送告警恢复.
        "
        ::= { rcftTraps 50 }

  rcftREDuplexTrap NOTIFICATION-TYPE
        OBJECTS {
           rcftInterfaceRDuplex

        }
        STATUS             current
        DESCRIPTION
       "
          远端模块以太网接口双工状态变化告警及恢复:由全双工变成半双工时发送告警,
          由半双工变成全双工时发送告警恢复.
       "
        ::= { rcftTraps 51 }

    rcftInterfaceRLinkTrap NOTIFICATION-TYPE
        OBJECTS {
           rcftInterfaceRLink
        }
        STATUS             current
        DESCRIPTION
        "
            远端模块以太网接口link状态变化告警及恢复:当由link状态由link up变为link down时发送告警,
            由link down变为link up时发送告警恢复
        "
        ::= { rcftTraps 52 }

   rcftSlotLALMTrap NOTIFICATION-TYPE
        OBJECTS {
           rcftSlotLALM
        }
        STATUS             current
        DESCRIPTION
       "
       局端端模块总告警.
       "
        ::= { rcftTraps 53 }


   rcftStmFiberRxPllUnlckTrap NOTIFICATION-TYPE
        OBJECTS {
           rcftStmFiberRxPllUnlck
        }
        STATUS             current
        DESCRIPTION
        "
        光口接收锁相环失锁告警及恢复.当光口rcftStmFiberRxPllUnlck状态由normal(1)变为alarm(2)
        时发送告警,由alarm(2)变为normal时发送告警恢复.
        "
        ::= { rcftTraps 54 }

   rcftStmFiberTxClkLosTrap NOTIFICATION-TYPE
        OBJECTS {
           rcftStmFiberTxClkLos
        }
        STATUS             current
        DESCRIPTION
        "
        光口发送时钟丢失告警及恢复.当光口发送时钟丢失状态rcftStmFiberTxClkLos由normal(1)变为alarm(2)
        时发送告警,由alarm(2)变为normal时发送告警恢复.
        "
        ::= { rcftTraps 55 }

   rcftStmFiberAnalogLosTrap NOTIFICATION-TYPE
        OBJECTS {
           rcftStmFiberAnalogLos
        }
        STATUS             current
        DESCRIPTION
         "
         光口模拟信号丢失告警及恢复.当光口模拟信号状态rcftStmFiberAnalogLos由normal(1)变为alarm(2)
         时发送告警,由alarm(2)变为normal时发送告警恢复.
         "
        ::= { rcftTraps 56 }

   rcftStmFiberDigitalLosTrap NOTIFICATION-TYPE
        OBJECTS {
           rcftStmFiberDigitalLos
        }
        STATUS             current
        DESCRIPTION
        "
         光口数字信号丢失告警及恢复.当光口数字信号状态rcftStmFiberDigitalLos由normal(1)变为alarm(2)
         时发送告警,由alarm(2)变为normal时发送告警恢复.
        "
        ::= { rcftTraps 57 }

    rcftStmFiberSyncLosTrap NOTIFICATION-TYPE
        OBJECTS {
           rcftStmFiberSyncLos
        }
        STATUS             current
        DESCRIPTION
        "
         光口帧失步告警及恢复.当光口帧失步状态rcftStmFiberSyncLos由normal(1)变为alarm(2)
         时发送告警,由alarm(2)变为normal时发送告警恢复.
        "
        ::= { rcftTraps 58 }

    rcftStmBncRxPllUnlckTrap NOTIFICATION-TYPE
        OBJECTS {
           rcftStmBncRxPllUnlck
        }
        STATUS             current
        DESCRIPTION
        "
        同轴电缆接口接收锁相环失锁告警及恢复.当同轴电缆接口锁相环状态rcftStmBncRxPllUnlck
        由normal(1)变为alarm(2)时发送告警,由alarm(2)变为normal时发送告警恢复.
        "
        ::= { rcftTraps 59 }

    rcftStmBncTxClkLosTrap NOTIFICATION-TYPE
        OBJECTS {
           rcftStmBncTxClkLos
        }
        STATUS             current
        DESCRIPTION
        "
        同轴电缆接口发送时钟丢失告警及恢复.当同轴电缆接口发送时钟丢失状态rcftStmBncTxClkLos
        由normal(1)变为alarm(2)时发送告警,由alarm(2)变为normal时发送告警恢复.
       "
        ::= { rcftTraps 60 }

    rcftStmBncAnalogLosTrap NOTIFICATION-TYPE
        OBJECTS {
           rcftStmBncAnalogLos
        }
        STATUS             current
        DESCRIPTION
        "
        同轴电缆接口模拟信号丢失告警及恢复.当同轴电缆接口模拟信号丢失状态rcftStmBncAnalogLos
        由normal(1)变为alarm(2)时发送告警,由alarm(2)变为normal时发送告警恢复.
        "
        ::= { rcftTraps 61 }

    rcftStmBncDigitalLosTrap NOTIFICATION-TYPE
        OBJECTS {
           rcftStmBncDigitalLos
        }
        STATUS             current
        DESCRIPTION
        "
        同轴电缆接口数字信号丢失告警及恢复.当同轴电缆接口数字信号丢失状态rcftStmBncDigitalLos
        由normal(1)变为alarm(2)时发送告警,由alarm(2)变为normal时发送告警恢复.
        "
        ::= { rcftTraps 62 }

    rcftStmBncSyncLosTrap NOTIFICATION-TYPE
        OBJECTS {
           rcftStmBncSyncLos
        }
        STATUS             current
        DESCRIPTION
        "
        同轴电缆接口帧失步告警及恢复.当同轴电缆接口帧失步状态rcftStmBncSyncLos
        由normal(1)变为alarm(2)时发送告警,由alarm(2)变为normal时发送告警恢复.
        "
        ::= { rcftTraps 63 }

   rcftInterfaceLOSTrap NOTIFICATION-TYPE
        OBJECTS {
           rcftInterfaceLOS
        }
        STATUS             current
        DESCRIPTION
        "接口LOS告警及恢复.当接口rcftInterfaceLOS状态由normal(1)变为alarm(2)时发送告警,
         由alarm(2)变为normal时发送告警恢复.
        "
        ::= { rcftTraps 64 }

   rcftInterfaceCVTrap NOTIFICATION-TYPE
        OBJECTS {
           rcftInterfaceCV
        }
        STATUS             current
        DESCRIPTION
        "接口CV告警及恢复.当接口rcftInterfaceCV状态由normal(1)变为alarm(2)时发送告警,
         由alarm(2)变为normal时发送告警恢复.
        "
        ::= { rcftTraps 65 }


   rcftInterfaceAISTrap NOTIFICATION-TYPE
        OBJECTS {
           rcftInterfaceAIS
        }
        STATUS             current
        DESCRIPTION
        "接口AIS告警及恢复.当接口rcftInterfaceAIS状态由normal(1)变为alarm(2)时发送告警,
         由alarm(2)变为normal时发送告警恢复.
        "
        ::= { rcftTraps 66 }

   rcftInterfaceLOFTrap NOTIFICATION-TYPE
        OBJECTS {
           rcftInterfaceLOF
        }
        STATUS             current
        DESCRIPTION
        "接口LOF告警及恢复.当接口rcftInterfaceLOF状态由normal(1)变为alarm(2)时发送告警,
         由alarm(2)变为normal时发送告警恢复.
        "
        ::= { rcftTraps 67 }

   rcftInterfaceCRCTrap NOTIFICATION-TYPE
        OBJECTS {
           rcftInterfaceCRC
        }
        STATUS             current
        DESCRIPTION
        "
         接口CRC告警及恢复.当接口rcftInterfaceCRC状态由normal(1)变为alarm(2)时发送告警,
         由alarm(2)变为normal时发送告警恢复.
        "
        ::= { rcftTraps 68 }

   rcftInterfaceE5Trap NOTIFICATION-TYPE
        OBJECTS {
           rcftInterfaceE5
        }
        STATUS             current
        DESCRIPTION
        "
         接口E5告警及恢复.当接口rcftInterfaceE5状态由normal(1)变为alarm(2)时发送告警,
         由alarm(2)变为normal时发送告警恢复.
        "
        ::= { rcftTraps 69 }

    rcftInterfaceRLOSTrap NOTIFICATION-TYPE
        OBJECTS {
           rcftInterfaceRLOS
        }
        STATUS             current
        DESCRIPTION
       "
         远端接口LOS告警及恢复.当远端接口rcftInterfaceRLOS状态由normal(1)变为alarm(2)时发送告警,
         由alarm(2)变为normal时发送告警恢复.
       "
        ::= { rcftTraps 70 }

   rcftInterfaceRCVTrap NOTIFICATION-TYPE
        OBJECTS {
           rcftInterfaceRCV
        }
        STATUS             current
        DESCRIPTION
        "
        远端接口CV告警及恢复.当远端接口rcftInterfaceRCV状态由normal(1)变为alarm(2)时发送告警,
         由alarm(2)变为normal时发送告警恢复.
        "
        ::= { rcftTraps 71 }


   rcftInterfaceRAISTrap NOTIFICATION-TYPE
        OBJECTS {
           rcftInterfaceRAIS
        }
        STATUS             current
        DESCRIPTION
        "
        远端接口AIS告警及恢复.当远端接口rcftInterfaceRAIS状态由normal(1)变为alarm(2)时发送告警,
         由alarm(2)变为normal时发送告警恢复.
        "
        ::= { rcftTraps 72 }

   rcftInterfaceRLOFTrap NOTIFICATION-TYPE
        OBJECTS {
           rcftInterfaceRLOF
        }
        STATUS             current
        DESCRIPTION
        "
        远端接口LOF告警及恢复.当远端接口rcftInterfaceRLOF状态由normal(1)变为alarm(2)时发送告警,
         由alarm(2)变为normal时发送告警恢复.
        "
        ::= { rcftTraps 73 }

   rcftInterfaceRCRCTrap NOTIFICATION-TYPE
        OBJECTS {
           rcftInterfaceRCRC
        }
        STATUS             current
        DESCRIPTION
        "
          远端接口CRC告警及恢复.当远端接口rcftInterfaceRCRC状态由normal(1)变为alarm(2)时发送告警,
         由alarm(2)变为normal时发送告警恢复.
        "
        ::= { rcftTraps 74 }

   rcftInterfaceLinkTrap NOTIFICATION-TYPE
        OBJECTS {
           rcftInterfaceLink
        }
        STATUS             current
        DESCRIPTION
        "
         本端接口LINKDOWN告警及恢复.当远端接口rcftInterfaceLink状态由link(1)变为unlink(2)时发送告警,
         由unlink(2)变为link时发送告警恢复.
        "
        ::= { rcftTraps 75 }

   rcftRSlotE1AISTrap NOTIFICATION-TYPE
        OBJECTS {
           rcftRSlotE1PortAlarm
        }
        STATUS             current
        DESCRIPTION
        "
          远端E1线路AIS告警及恢复.
        "
        ::= { rcftTraps 76 }

  rcftRSlotE1LOFTRAP NOTIFICATION-TYPE
       OBJECTS {
          rcftRSlotE1PortAlarm
       }
       STATUS  current
       DESCRIPTION
       "
         远端E1线路LOF告警及恢复
       "
       ::={ rcftTraps 77}

  rcftRSlotE1CRCTRAP NOTIFICATION-TYPE
       OBJECTS {
          rcftRSlotE1PortAlarm
       }
       STATUS  current
       DESCRIPTION
       "
         远端E1线路CRC告警及恢复
       "
       ::={ rcftTraps 78}

   rcftRSlotRALMTrap NOTIFICATION-TYPE
        OBJECTS {
            rcftRSlotE1PortAlarm
        }
        STATUS             current
        DESCRIPTION
        "
          远端E1线路远端模块总告警及恢复.
        "
        ::= { rcftTraps 79 }

   rcftRSlotLALMTrap NOTIFICATION-TYPE
        OBJECTS {
          rcftV35E1PortExtendStatus
        }
        STATUS             current
        DESCRIPTION
        "
         远端模块局端总告警及恢复.
        "
        ::= { rcftTraps 80 }

    cwdmTransmitLOLTrap NOTIFICATION-TYPE
    	OBJECTS{
    	    rcftSlotWorkStatus
    	}
    	STATUS current
    	DESCRIPTION
    	"
    	   发送通道信号失锁告警及恢复(CWDM←CLIEN )
    	"
        ::= { rcftTraps 81 }

     cwdmTransmitLOATrap NOTIFICATION-TYPE
     	OBJECTS{
     	     rcftSlotWorkStatus
     	}
    	STATUS current
    	DESCRIPTION
    	"
    	   发送通道信号无效告警及恢复(CWDM←CLIENT)
    	"
        ::= { rcftTraps 82 }

    cwdmReceiveLOLTrap NOTIFICATION-TYPE
    	OBJECTS{
    	    rcftSlotWorkStatus
    	}
    	STATUS current
    	DESCRIPTION
    	"
    	   接收通道信号失锁告警及恢复(CWDM→CLIENT)
    	"
        ::= { rcftTraps 83 }

     cwdmReceiveLOATrap NOTIFICATION-TYPE
     	OBJECTS{
     	     rcftSlotWorkStatus
     	}
    	STATUS current
    	DESCRIPTION
    	"
    	   接收通道信号无效告警及恢复(CWDM→CLIENT)
    	"
        ::= { rcftTraps 84 }


     cwdmCWDMLaserTxfaultTrap NOTIFICATION-TYPE
     	OBJECTS{
     	     cwdmCWDMWorkStatus
     	}
     	STATUS current
     	DESCRIPTION
     	"
     	   CWDM侧激光器发送失效告警及恢复
     	"
     	::= { rcftTraps 85 }

   cwdmCWDMInputSignalLosTrap NOTIFICATION-TYPE
     	OBJECTS{
     	     cwdmCWDMWorkStatus
     	}
     	STATUS current
     	DESCRIPTION
     	"
     	   CWDM侧输入信号丢失告警及恢复
     	"
     	::= { rcftTraps 86 }


    cwdmCWDMModuleExistTrap NOTIFICATION-TYPE
      OBJECTS{
        cwdmCWDMWorkStatus
      }
      STATUS current
      DESCRIPTION
      "
        CWDM侧模块不在位告警及恢复
      "
     ::= { rcftTraps 87 }

     cwdmClientLaserTxfaultTrap NOTIFICATION-TYPE
     	OBJECTS{
     	     cwdmClientWorkStatus
     	}
     	STATUS current
     	DESCRIPTION
     	"
     	   Client侧激光器发送失效告警及恢复
     	"
     	::= { rcftTraps 88 }

   cwdmClientInputSignalLosTrap NOTIFICATION-TYPE
     	OBJECTS{
     	     cwdmClientWorkStatus
     	}
     	STATUS current
     	DESCRIPTION
     	"
     	   client侧输入信号丢失告警及恢复
     	"
     	::= { rcftTraps 89 }


    cwdmClientModuleExistTrap NOTIFICATION-TYPE
      OBJECTS{
        cwdmClientWorkStatus
      }
      STATUS current
      DESCRIPTION
      "
        client侧模块不在位告警及恢复
      "
     ::= { rcftTraps 90 }


    rcftRSlotORLnkTrap  NOTIFICATION-TYPE
    	OBJECTS{
    	    rcftRSlotORLnk
    	}
    	STATUS    current
    	DESCRIPTION
    	"
    	  远端光口接收LINK告警及恢复
    	"
    	::= {rcftTraps 91}


    rcftRSlotOTLnkTrap  NOTIFICATION-TYPE
    	OBJECTS{
    	    rcftRSlotOTLnk
    	}
    	STATUS    current
    	DESCRIPTION
    	"
    	  远端光口发送LINK告警及恢复
    	"
    	::= {rcftTraps 92}

    cwdmSpeedUnmatchedTrap NOTIFICATION-TYPE
    	OBJECTS{
    		rcftSlotWorkStatus
    	}
    	STATUS current
    	DESCRIPTION
    	"
           cwdm速率不匹配告警及恢复.
    	"
    	::= {rcftTraps 93}

    remotecwdmCWDMLaserTxfaultTrap NOTIFICATION-TYPE
     	OBJECTS{
     	     cwdmCWDMWorkStatus
     	}
     	STATUS current
     	DESCRIPTION
     	"
     	   远端设备CWDM侧激光器发送失效告警及恢复
     	"
     	::= { rcftTraps 94 }

   remotecwdmCWDMInputSignalLosTrap NOTIFICATION-TYPE
     	OBJECTS{
     	     cwdmCWDMWorkStatus
     	}
     	STATUS current
     	DESCRIPTION
     	"
     	   远端设备CWDM侧输入信号丢失告警及恢复
     	"
     	::= { rcftTraps 95 }

    remotecwdmCWDMModuleExistTrap NOTIFICATION-TYPE
      OBJECTS{
        cwdmCWDMWorkStatus
      }
      STATUS current
      DESCRIPTION
      "
        远端设备CWDM侧模块不在位告警及恢复
      "
     ::= { rcftTraps 96 }


 	rcftSlotE1LOMFTrap	NOTIFICATION-TYPE
 		OBJECTS{
 			   rcftSlotE1PortAlarm
 		}
      STATUS current
      DESCRIPTION
      "
      	 本端E1线路复帧失步LOMF告警及恢复
      "
      ::= { rcftTraps 97 }

     rcftRSlotE1LOMFTrap NOTIFICATION-TYPE
 		OBJECTS{
 			   rcftRSlotE1PortAlarm
 		}
      STATUS current
      DESCRIPTION
      "
      	 远端E1线路复帧失步LOMF告警及恢复
      "
      ::= { rcftTraps 98 }

     rcftSlotE1CVTrap	NOTIFICATION-TYPE
     	OBJECTS{
     		  rcftSlotE1PortAlarm
     	}
      STATUS current
      DESCRIPTION
      "
      	 本端E1线路CV告警及恢复
      "
      ::= { rcftTraps 99 }


      rcftRSlotE1CVTrap	NOTIFICATION-TYPE
     	OBJECTS{
     		  rcftRSlotE1PortAlarm
     	}
      STATUS current
      DESCRIPTION
      "
      	 远端E1线路CV告警及恢复
      "
      ::= { rcftTraps 100 }

      rcftSlotSHDSLLosTrap	NOTIFICATION-TYPE
      	OBJECTS{
    	        rcftFxWorkStatus
      	}
      STATUS current
      DESCRIPTION
      "
      	局端模块G.SHDSL口的LOS告警及恢复
      "
      ::= { rcftTraps 101 }

      rcftSlotSHDSLLOFTrap	NOTIFICATION-TYPE
      	OBJECTS{
   	        rcftFxWorkStatus
      	}
      STATUS current
      DESCRIPTION
      "
      	局端模块G.SHDSL口的LOF告警及恢复
      "
      ::= { rcftTraps 102 }

      rcftRSlotSHDSLLosTrap	NOTIFICATION-TYPE
      	OBJECTS{
   	        rcftFxWorkStatus
      	}
      STATUS current
      DESCRIPTION
      "
      	远端模块G.SHDSL口的LOS告警及恢复
      "
      ::= { rcftTraps 103 }

      rcftRSlotSHDSLLOFTrap	NOTIFICATION-TYPE
      	OBJECTS{
   	        rcftFxWorkStatus
      	}
      STATUS current
      DESCRIPTION
      "
      	远端模块G.SHDSL口的LOF告警及恢复
      "
      ::= { rcftTraps 104 }

     rcftSlotSHDSLLinkTrap NOTIFICATION-TYPE
     	OBJECTS{
 	          rcftSlotOLink
     	}
     	STATUS	current
     	DESCRIPTION
     	"
      	   局端模块G.SHDSL口的Link告警及恢复
     	"
        ::= { rcftTraps 105 }

     rcftRSlotSHDSLLinkTrap NOTIFICATION-TYPE
     	OBJECTS{
         rcftRSlotOLink
     	}
     	STATUS	current
     	DESCRIPTION
     	"
      	远端模块G.SHDSL口的Link告警及恢复
     	"
        ::= { rcftTraps 106 }

     rcftClientOLinkTrap NOTIFICATION-TYPE
        OBJECTS {
           rcftFxWorkStatus
        }
        STATUS             current
        DESCRIPTION
        "
          局端用户侧光口LINKDOWN告警及恢复.

        "
        ::= { rcftTraps 107 }

     rcftClientOSDTrap NOTIFICATION-TYPE
        OBJECTS {
          rcftFxWorkStatus
        }
        STATUS     current
        DESCRIPTION
        "
         本地光模块用户侧SD输出信号异常告警和恢复.
        "
        ::={ rcftTraps 108 }


     rcftRClientOLinkTrap NOTIFICATION-TYPE
        OBJECTS {
           rcftFxWorkStatus
        }
        STATUS             current
        DESCRIPTION
        "
            远端用户侧光口LINKDOWN告警及恢复.
        "
        ::= { rcftTraps 109 }

     rcftRClientOSDTrap NOTIFICATION-TYPE
        OBJECTS {
           rcftFxWorkStatus
        }
        STATUS     current
        DESCRIPTION
        "
         远端光模块用户侧SD输出信号异常告警及恢复.
        "
        ::={ rcftTraps 110 }

   cwdmPrimaryCWDMInputSignalLosTrap NOTIFICATION-TYPE
        OBJECTS {
     	     cwdmCWDMWorkStatus
        }
        STATUS     current
        DESCRIPTION
        "
     	   主用通道CWDM侧输入信号丢失告警及恢复
        "
        ::={ rcftTraps 111 }

    cwdmPrimaryCWDMModuleExistTrap NOTIFICATION-TYPE
        OBJECTS {
        	cwdmCWDMWorkStatus
        }
        STATUS     current
        DESCRIPTION
        "
        主用通道CWDM侧模块不在位告警及恢复
        "
        ::={ rcftTraps 112 }

     rcftSlotPSChannelOTrap NOTIFICATION-TYPE
        OBJECTS {
          rcftSlotOpticalDeviceStatus
        }
        STATUS     current
        DESCRIPTION
        "
          作为从主用到备用光通道的切换的事件告警，只有告警，没有恢复。
          要想清除告警只有让用户手动清除
        "
        ::={ rcftTraps 113 }

      rcftInterfaceRELinkTrap NOTIFICATION-TYPE
        OBJECTS {
           rcftInterfaceRLink
        }
        STATUS             current
        DESCRIPTION
        "
            远端模块以太网接口link状态变化告警及恢复:当由link状态由link up变为link down时发送告警,
            由link down变为link up时发送告警恢复
        "
        ::= { rcftTraps 114 }

    cwdmSecondaryReceiveLOLTrap NOTIFICATION-TYPE
    	OBJECTS{
    	    rcftSlotWorkStatus
    	}
    	STATUS current
    	DESCRIPTION
    	"
    	   备用通道接收通道信号失锁告警及恢复(CWDM→CLIENT
    	"
        ::= { rcftTraps 115 }

   cwdmSecondaryCWDMInputSignalLosTrap NOTIFICATION-TYPE
     	OBJECTS{
     	     cwdmCWDMWorkStatus
     	}
     	STATUS current
     	DESCRIPTION
     	"
     	   备用通道CWDM侧输入信号丢失告警及恢复
     	"
     	::= { rcftTraps 116 }

    cwdmSecondaryCWDMModuleExistTrap NOTIFICATION-TYPE
      	OBJECTS{
        	cwdmCWDMWorkStatus
      	}
      	STATUS current
     	DESCRIPTION
      	"
        备用通道CWDM侧模块不在位告警及恢复
      	"
     	::= { rcftTraps 117 }

    rcftInterfaceLToRLOSTrap NOTIFICATION-TYPE
        OBJECTS {
           rcftInterfaceRLOS
        }
        STATUS             current
        DESCRIPTION
       "
         通过局端看到的远端接口LOS告警及恢复.当远端接口rcftInterfaceRLOS状态由normal(1)变为alarm(2)时发送告警,
         由alarm(2)变为normal时发送告警恢复.
       "
        ::= { rcftTraps 118 }

   rcftInterfaceLtoRAISTrap NOTIFICATION-TYPE
        OBJECTS {
           rcftInterfaceRAIS
        }
        STATUS             current
        DESCRIPTION
        "
        通过局端看到的远端接口AIS告警及恢复.当远端接口rcftInterfaceRAIS状态由normal(1)变为alarm(2)时发送告警,
         由alarm(2)变为normal时发送告警恢复.
        "
        ::= { rcftTraps 119 }

   rcftInterfaceLtoRLOFTrap NOTIFICATION-TYPE
        OBJECTS {
           rcftInterfaceRLOF
        }
        STATUS             current
        DESCRIPTION
        "
        通过局端看到的远端接口LOF告警及恢复.当远端接口rcftInterfaceRLOF状态由normal(1)变为alarm(2)时发送告警,
         由alarm(2)变为normal时发送告警恢复.
        "
        ::= { rcftTraps 120 }

   rcftInterfaceLtoRCRCTrap NOTIFICATION-TYPE
        OBJECTS {
           rcftInterfaceRCRC
        }
        STATUS             current
        DESCRIPTION
        "
         通过局端看到的远端接口CRC告警及恢复.当远端接口rcftInterfaceRCRC状态由normal(1)变为alarm(2)时发送告警,
         由alarm(2)变为normal时发送告警恢复.
        "
        ::= { rcftTraps 121 }

    rcftSlotRemotePowerDownTrap NOTIFICATION-TYPE
      	OBJECTS{
        	rcftSlotLineStatus
      	}
      	STATUS current
     	DESCRIPTION
      	"
           远端设备掉电告警
      	"
     	::= { rcftTraps 122 }

     rcftSlotVideoLosTrap  NOTIFICATION-TYPE
      	OBJECTS{
        	rcftFxWorkStatus
      	}
      	STATUS current
     	DESCRIPTION
      	"
           局端设备视频信号los告警
      	"
     	::= { rcftTraps 123 }

     rcftRSlotVideoLosTrap  NOTIFICATION-TYPE
      	OBJECTS{
        	rcftFxWorkStatus
      	}
      	STATUS current
     	DESCRIPTION
      	"
           局端设备视频信号los告警
      	"
     	::= { rcftTraps 124 }

      rcftSlotLocalToRemoteE1CRCTrap	NOTIFICATION-TYPE
      	OBJECTS{
			rcftSlotE1PortAlarm
      	}
      	STATUS current
     	DESCRIPTION
     	"
     		在局端设备上表现的远端设备E1接口的CRC告警
     	"
     	::= { rcftTraps 125 }

      rcftSlotLocalToRemoteE1LOFTrap	NOTIFICATION-TYPE
      	OBJECTS{
			rcftSlotE1PortAlarm
      	}
      	STATUS current
     	DESCRIPTION
     	"
     		在局端设备上表现的远端设备E1接口的LOF告警
     	"
     	::= { rcftTraps 126 }

      rcftSlotLocalToRemoteE1AISTrap	NOTIFICATION-TYPE
      	OBJECTS{
			rcftSlotE1PortAlarm
      	}
      	STATUS current
     	DESCRIPTION
     	"
     		在局端设备上表现的远端设备E1接口的AIS告警
     	"
     	::= { rcftTraps 127 }

      rcftSlotLocalToRemoteE1LOSTrap	NOTIFICATION-TYPE
      	OBJECTS{
			rcftSlotE1PortAlarm
      	}
      	STATUS current
     	DESCRIPTION
     	"
     		在局端设备上表现的远端设备E1接口的LOS告警
     	"
     	::= { rcftTraps 128 }

    cwdmPrimaryReceiveLOLTrap NOTIFICATION-TYPE
    	OBJECTS{
    	    rcftSlotWorkStatus
    	}
    	STATUS current
    	DESCRIPTION
    	"
    	   主用通道接收通道信号失锁告警及恢复(CWDM→CLIENT
    	"
        ::= { rcftTraps 129 }

     rcftClientPortLOLTrap	NOTIFICATION-TYPE
    	OBJECTS{
    	    rcftSlotWorkStatus
    	}
    	STATUS current
    	DESCRIPTION
    	"
    		客户侧信号失锁告警及恢复
    	"
        ::= { rcftTraps 130 }

     rcftLinePortLOLTrap	NOTIFICATION-TYPE
    	OBJECTS{
    	    rcftSlotWorkStatus
    	}
    	STATUS current
    	DESCRIPTION
    	"
    		线路侧信号失锁告警及恢复
    	"
        ::= { rcftTraps 131 }

     rcftSlotSPChannelOTrap NOTIFICATION-TYPE
        OBJECTS {
          rcftSlotOpticalDeviceStatus
        }
        STATUS     current
        DESCRIPTION
        "
          作为从备用到主用光通道的切换的事件告警，只有告警，没有恢复。
          要想清除告警只有让用户手动清除
        "
        ::={ rcftTraps 132 }

      rcftSaveConfigFileFinishedTrap NOTIFICATION-TYPE
      	STATUS	current
      	DESCRIPTION
      	"
      		作为配置信息保存结束的事件告警，只有告警，没有恢复。
      	"
        ::={ rcftTraps 133 }

      rcftRSlotLinePortLOLTrap  NOTIFICATION-TYPE
    	OBJECTS{
    	    rcftSlotWorkStatus
    	}
    	STATUS current
    	DESCRIPTION
    	"
    		远端模块信号失锁告警及恢复
    	"
        ::= { rcftTraps 134 }

      rcftSlotSFPModuleTempHighTrap  NOTIFICATION-TYPE
    	OBJECTS{
    	    rcftSlotSFPDiagnosticsInfo
    	}
    	STATUS current
    	DESCRIPTION
    	"
    		SFP模块温度上限告警
    	"
        ::= { rcftTraps 135 }

      rcftSlotSFPModuleTempLowTrap  NOTIFICATION-TYPE
    	OBJECTS{
    	    rcftSlotSFPDiagnosticsInfo
    	}
    	STATUS current
    	DESCRIPTION
    	"
    		SFP模块温度下限告警
    	"
        ::= { rcftTraps 136 }

      rcftSlotSFPModuleVoltageHighTrap  NOTIFICATION-TYPE
    	OBJECTS{
    	    rcftSlotSFPDiagnosticsInfo
    	}
    	STATUS current
    	DESCRIPTION
    	"
    		SFP模块电压上限告警
    	"
        ::= { rcftTraps 137 }

      rcftSlotSFPModuleVoltageLowTrap  NOTIFICATION-TYPE
    	OBJECTS{
    	    rcftSlotSFPDiagnosticsInfo
    	}
    	STATUS current
    	DESCRIPTION
    	"
    		SFP模块电压下限告警
    	"
        ::= { rcftTraps 138 }

      rcftSlotSFPModuleOffsetCurrHighTrap  NOTIFICATION-TYPE
    	OBJECTS{
    	    rcftSlotSFPDiagnosticsInfo
    	}
    	STATUS current
    	DESCRIPTION
    	"
    		SFP模块电流上限告警
    	"
        ::= { rcftTraps 139 }

      rcftSlotSFPModuleOffsetCurrLowTrap  NOTIFICATION-TYPE
    	OBJECTS{
    	    rcftSlotSFPDiagnosticsInfo
    	}
    	STATUS current
    	DESCRIPTION
    	"
    		SFP模块电流下限告警
    	"
        ::= { rcftTraps 140 }

      rcftSlotSFPModuleSendPowerHighTrap  NOTIFICATION-TYPE
    	OBJECTS{
    	    rcftSlotSFPDiagnosticsInfo
    	}
    	STATUS current
    	DESCRIPTION
    	"
    		SFP模块发光功率上限告警
    	"
        ::= { rcftTraps 141 }

      rcftSlotSFPModuleSendPowerLowTrap  NOTIFICATION-TYPE
    	OBJECTS{
    	    rcftSlotSFPDiagnosticsInfo
    	}
    	STATUS current
    	DESCRIPTION
    	"
    		SFP模块发光功率下限告警
    	"
        ::= { rcftTraps 142 }

      rcftSlotSFPModuleRecvPowerHighTrap  NOTIFICATION-TYPE
    	OBJECTS{
    	    rcftSlotSFPDiagnosticsInfo
    	}
    	STATUS current
    	DESCRIPTION
    	"
    		SFP模块收光功率上限告警
    	"
        ::= { rcftTraps 143 }

      rcftSlotSFPModuleRecvPowerLowTrap  NOTIFICATION-TYPE
    	OBJECTS{
    	    rcftSlotSFPDiagnosticsInfo
    	}
    	STATUS current
    	DESCRIPTION
    	"
    		SFP模块收光功率下限告警
    	"
        ::= { rcftTraps 144 }

      rcftRSlotSFPModuleTempHighTrap  NOTIFICATION-TYPE
    	OBJECTS{
    	    rcftRSlotSFPDiagnosticsInfo
    	}
    	STATUS current
    	DESCRIPTION
    	"
    		SFP模块温度上限告警
    	"
        ::= { rcftTraps 145 }

      rcftRSlotSFPModuleTempLowTrap  NOTIFICATION-TYPE
    	OBJECTS{
    	    rcftRSlotSFPDiagnosticsInfo
    	}
    	STATUS current
    	DESCRIPTION
    	"
    		SFP模块温度下限告警
    	"
        ::= { rcftTraps 146 }

      rcftRSlotSFPModuleVoltageHighTrap  NOTIFICATION-TYPE
    	OBJECTS{
    	    rcftRSlotSFPDiagnosticsInfo
    	}
    	STATUS current
    	DESCRIPTION
    	"
    		SFP模块电压上限告警
    	"
        ::= { rcftTraps 147 }

      rcftRSlotSFPModuleVoltageLowTrap  NOTIFICATION-TYPE
    	OBJECTS{
    	    rcftRSlotSFPDiagnosticsInfo
    	}
    	STATUS current
    	DESCRIPTION
    	"
    		SFP模块电压下限告警
    	"
        ::= { rcftTraps 148 }

      rcftRSlotSFPModuleOffsetCurrHighTrap  NOTIFICATION-TYPE
    	OBJECTS{
    	    rcftRSlotSFPDiagnosticsInfo
    	}
    	STATUS current
    	DESCRIPTION
    	"
    		SFP模块电流上限告警
    	"
        ::= { rcftTraps 149 }

      rcftRSlotSFPModuleOffsetCurrLowTrap  NOTIFICATION-TYPE
    	OBJECTS{
    	    rcftRSlotSFPDiagnosticsInfo
    	}
    	STATUS current
    	DESCRIPTION
    	"
    		SFP模块电流下限告警
    	"
        ::= { rcftTraps 150 }

      rcftRSlotSFPModuleSendPowerHighTrap  NOTIFICATION-TYPE
    	OBJECTS{
    	    rcftRSlotSFPDiagnosticsInfo
    	}
    	STATUS current
    	DESCRIPTION
    	"
    		SFP模块发光功率上限告警
    	"
        ::= { rcftTraps 151 }

      rcftRSlotSFPModuleSendPowerLowTrap  NOTIFICATION-TYPE
    	OBJECTS{
    	    rcftRSlotSFPDiagnosticsInfo
    	}
    	STATUS current
    	DESCRIPTION
    	"
    		SFP模块发光功率下限告警
    	"
        ::= { rcftTraps 152 }

      rcftRSlotSFPModuleRecvPowerHighTrap  NOTIFICATION-TYPE
    	OBJECTS{
    	    rcftRSlotSFPDiagnosticsInfo
    	}
    	STATUS current
    	DESCRIPTION
    	"
    		SFP模块收光功率上限告警
    	"
        ::= { rcftTraps 153 }

      rcftRSlotSFPModuleRecvPowerLowTrap  NOTIFICATION-TYPE
    	OBJECTS{
    	    rcftRSlotSFPDiagnosticsInfo
    	}
    	STATUS current
    	DESCRIPTION
    	"
    		SFP模块收光功率下限告警
    	"
        ::= { rcftTraps 154 }

      rcftSlotTempHighLimitTrap		NOTIFICATION-TYPE
      OBJECTS {
      		rcftSlotTempHighLimit
      }
      STATUS current
      DESCRIPTION
      "
    		温度超上限告警
      "
      ::= { rcftTraps 155 }

      rcftSlotTempLowLimitTrap		NOTIFICATION-TYPE
      OBJECTS {
      		rcftSlotTempLowLimit
      }
      STATUS current
      DESCRIPTION
      "
    		温度超下限告警
      "
      ::= { rcftTraps 156 }

      rcftSlotHumidityHighLimitTrap		NOTIFICATION-TYPE
      OBJECTS {
      		rcftSlotHumidityHighLimit
      }
      STATUS current
      DESCRIPTION
      "
    		湿度超上限告警
      "
      ::= { rcftTraps 157 }

      rcftSlotHumidityLowLimitTrap		NOTIFICATION-TYPE
      OBJECTS {
      		rcftSlotHumidityLowLimit
      }
      STATUS current
      DESCRIPTION
      "
    		湿度超下限告警
      "
      ::= { rcftTraps 158 }

      rcftSlotPSChannelTrap		NOTIFICATION-TYPE
      OBJECTS {
      		rcftSlotOpticalDeviceStatus
      }
      STATUS current
      DESCRIPTION
      "
    		主用通道切换到备用通道告警（没有恢复）
      "
      ::= { rcftTraps 159 }

      rcftSlotSPChannelTrap		NOTIFICATION-TYPE
      OBJECTS {
      		rcftSlotOpticalDeviceStatus
      }
      STATUS current
      DESCRIPTION
      "
    		备用通道切换到主用通道告警（没有恢复）
      "
      ::= { rcftTraps 160 }

       rcftSlotE1TransErrorCodeMore10E-3 NOTIFICATION-TYPE
       OBJECTS {
          rcftSlotOTransErrorCode
       }
       STATUS  current
       DESCRIPTION
        "
        本端模块E1传输误码率大于10E-3告警
        "
       ::={ rcftTraps 161}

  	rcftSlotE1TransErrorCodeMore10E-6 NOTIFICATION-TYPE
       OBJECTS {
          rcftSlotOTransErrorCode
       }
       STATUS  current
       DESCRIPTION
     "
     本端模块E1传输误码率大于10E-6告警
     "
       ::={ rcftTraps 162}



END
