-- MibName=raisecomRcmp
RAISECOM-RCMP-MIB DEFINITIONS ::= BEGIN

IMPORTS
    MODULE-IDENTITY, OBJECT-TYPE     FROM SNMPv2-SMI
    MacAddress,
    RowStatus          		     FROM SNMPv2-TC
    EnableVar					FROM SWITCH-TC
    raisecomCluster				FROM RAISECOM-BASE-MIB;

raisecomRcmp MODULE-IDENTITY
    LAST-UPDATED "0412210000Z"
    ORGANIZATION "IETF SNMPv2 Working Group"
    CONTACT-INFO
            "
             Phone:  01082884499
             Email:  support@raisecom.com"
    DESCRIPTION
            "The MIB module for managing  rcmp protocol."
    REVISION      "0412210000Z"
    DESCRIPTION
            ""
    ::= {raisecomCluster 1}

raisecomRcmpClusterEnable OBJECT-TYPE
     SYNTAX  EnableVar
     ACCESS read-write
     STATUS current
     DESCRIPTION
        "DURABLE: enable(1) or disable(2) rcmp protocol on the switch."
     DEFVAL  { disable }
        ::= { raisecomRcmp 1 }


raisecomRcmpIdentity OBJECT-TYPE
    SYNTAX      INTEGER {
                    member(1),
                    candidate(2),
                    commander(3)
                    }
    MAX-ACCESS  read-only
    STATUS      current
    DESCRIPTION
            "The identity of the switch."
    ::= { raisecomRcmp 2 }

raisecomRcmpCommanderMac OBJECT-TYPE
    SYNTAX      MacAddress
    MAX-ACCESS  read-only
    STATUS      current
    DESCRIPTION
            "The mac address of the commander."
    ::= { raisecomRcmp 3 }

raisecomRcmpAutoActiveEnable OBJECT-TYPE
    SYNTAX  EnableVar
    MAX-ACCESS  read-write
    STATUS      current
    DESCRIPTION
            "Enable auto active function."
    DEFVAL  { disable }
    ::= { raisecomRcmp 4 }

raisecomRcmpAutoActiveCommanderMac OBJECT-TYPE
    SYNTAX      MacAddress
    MAX-ACCESS  read-write
    STATUS      current
    DESCRIPTION
            "The mac address of the commander that can auto active it'self."
    ::= { raisecomRcmp 5 }


-- raisecomRcmpMemberTable

raisecomRcmpMemberTable OBJECT-TYPE
    SYNTAX      SEQUENCE OF RaisecomRcmpMemberEntry
    MAX-ACCESS  not-accessible
    STATUS      current
    DESCRIPTION
            "Cluster member talbe."
    ::= { raisecomRcmp 6 }

raisecomRcmpMemberEntry OBJECT-TYPE
    SYNTAX      RaisecomRcmpMemberEntry
    MAX-ACCESS  not-accessible
    STATUS      current
    DESCRIPTION
            "Cluster member table entry."
    INDEX   {raisecomRcmpMacAddress}
    ::= { raisecomRcmpMemberTable 1 }

RaisecomRcmpMemberEntry ::= SEQUENCE {
        raisecomRcmpMacAddress 		MacAddress,
        raisecomRcmpHostName     	OCTET STRING,
        raisecomRcmpActiveEnable   	EnableVar,
        raisecomRcmpOperationState	INTEGER,
        raisecomRcmpUdpPortNumber    	INTEGER,
        raisecomRcmpUserName		OCTET STRING,
        raisecomRcmpPassword		OCTET STRING,
        raisecomRcmpRowStatus		RowStatus
        }

raisecomRcmpMacAddress OBJECT-TYPE
    SYNTAX      MacAddress
    MAX-ACCESS  read-only
    STATUS      current
    DESCRIPTION
    "The mac addr of the member."
    ::= { raisecomRcmpMemberEntry 1 }

raisecomRcmpHostName OBJECT-TYPE
    SYNTAX    OCTET STRING
    MAX-ACCESS  read-only
    STATUS      current
    DESCRIPTION
            "The hostname of the member."
    ::= { raisecomRcmpMemberEntry 2 }

raisecomRcmpActiveEnable OBJECT-TYPE
    SYNTAX  EnableVar
    MAX-ACCESS read-write
    STATUS current
    DESCRIPTION
        "The hostname of the member."
    ::=  { raisecomRcmpMemberEntry 3 }

raisecomRcmpOperationState OBJECT-TYPE
    SYNTAX  INTEGER {
                 down(1),
                 up(2)
                }
    MAX-ACCESS read-only
    STATUS current
    DESCRIPTION
        "The operation state of the member."
    ::=  { raisecomRcmpMemberEntry 4 }

raisecomRcmpUdpPortNumber OBJECT-TYPE
    SYNTAX  INTEGER
    MAX-ACCESS read-only
    STATUS current
    DESCRIPTION
        "The udp port of the member."
    ::=  { raisecomRcmpMemberEntry 5 }

raisecomRcmpUserName OBJECT-TYPE
    SYNTAX   OCTET STRING (SIZE (1..16))
    MAX-ACCESS read-write
    STATUS current
    DESCRIPTION
        "The user name of the member."
    ::=  { raisecomRcmpMemberEntry 6 }

raisecomRcmpPassword OBJECT-TYPE
    SYNTAX   OCTET STRING (SIZE (1..48))
    MAX-ACCESS read-write
    STATUS current
    DESCRIPTION
        "The password of the member."
    ::=  { raisecomRcmpMemberEntry 7 }

raisecomRcmpRowStatus OBJECT-TYPE
    SYNTAX  RowStatus
    MAX-ACCESS read-create
    STATUS current
    DESCRIPTION
        "The row status  of the member table."
    ::=  { raisecomRcmpMemberEntry 8 }

raisecomRcmpSessionTimeout OBJECT-TYPE
    SYNTAX      INTEGER (120..600)
    MAX-ACCESS  read-write
    STATUS      current
    DESCRIPTION
            "Cluster session timeout time."
    ::= { raisecomRcmp 7 }

raisecomRcmpMaxSession OBJECT-TYPE
    SYNTAX      INTEGER (1..2048)
    MAX-ACCESS  read-write
    STATUS      current
    DESCRIPTION
            "Max sessions of the Cluster."
    ::= { raisecomRcmp 8 }

raisecomRcmpMaxSessionPerMember OBJECT-TYPE
    SYNTAX      INTEGER (1..50)
    MAX-ACCESS  read-write
    STATUS      current
    DESCRIPTION
            "Max sessions of a  cluster member."
    ::= { raisecomRcmp 9 }

raisecomRcmpMaxMember OBJECT-TYPE
    SYNTAX      INTEGER (1..512)
    MAX-ACCESS  read-write
    STATUS      current
    DESCRIPTION
            "Max number of the Cluster member."
    ::= { raisecomRcmp 10 }

raisecomRcmpID OBJECT-TYPE
    SYNTAX      MacAddress
    MAX-ACCESS  read-only
    STATUS      current
    DESCRIPTION
            "Cluster member ID."
    ::= { raisecomRcmp 11 }

raisecomRcmpStatisticsTotalSession OBJECT-TYPE
    SYNTAX      Counter
    MAX-ACCESS  read-only
    STATUS      current
    DESCRIPTION
            "Total cluster sessions."
    ::= { raisecomRcmp 12 }

raisecomRcmpStatisticsCurrentSession OBJECT-TYPE
    SYNTAX      Counter
    MAX-ACCESS  read-only
    STATUS      current
    DESCRIPTION
            "current cluster sessions."
    ::= { raisecomRcmp 13 }

raisecomRcmpStatisticsMaxSession OBJECT-TYPE
    SYNTAX      Counter
    MAX-ACCESS  read-only
    STATUS      current
    DESCRIPTION
            "max cluster sessions."
    ::= { raisecomRcmp 14 }

raisecomRcmpStatisticsTimeoutSession OBJECT-TYPE
    SYNTAX      Counter
    MAX-ACCESS  read-only
    STATUS      current
    DESCRIPTION
            "timeout cluster sessions."
    ::= { raisecomRcmp 15 }

raisecomRcmpStatisticsInPkts OBJECT-TYPE
    SYNTAX      Counter
    MAX-ACCESS  read-only
    STATUS      current
    DESCRIPTION
            "incoming cluster  packets."
    ::= { raisecomRcmp 16 }

raisecomRcmpStatisticsOutPkts OBJECT-TYPE
    SYNTAX      Counter
    MAX-ACCESS  read-only
    STATUS      current
    DESCRIPTION
            "outgoing cluster  packets."
    ::= { raisecomRcmp 17 }

raisecomRcmpStatisticsDiscardPkts OBJECT-TYPE
    SYNTAX      Counter
    MAX-ACCESS  read-only
    STATUS      current
    DESCRIPTION
            "discard cluster  packets."
    ::= { raisecomRcmp 18 }

raisecomRcmpStatisticsErrorPkts OBJECT-TYPE
    SYNTAX      Counter
    MAX-ACCESS  read-only
    STATUS      current
    DESCRIPTION
            "error cluster packets."
    ::= { raisecomRcmp 19 }

raisecomRcmpDefaultVlan   OBJECT-TYPE
    SYNTAX      INTEGER
    MAX-ACCESS  read-only
    STATUS      current
    DESCRIPTION
            "default vlan for cluster."
    ::= { raisecomRcmp 20 }

raisecomRcmpClearStatistics OBJECT-TYPE
    SYNTAX  INTEGER {
                 clear(1)
               }
    MAX-ACCESS  read-write
    STATUS      current
    DESCRIPTION
            "clear statistics."
    ::= { raisecomRcmp 21 }
END
