-- File: RC002-REMOTE-DEVICE-MIB.my
-- Changes:
-- author:SunSuli
-- remote card including RC952-EE1,RC952-FXE1,RC601,RC501,RC511


  RC002-REMOTE-DEVICE-MIB   DEFINITIONS ::= BEGIN

   IMPORTS
		IpAddress,
		OBJECT-TYPE, MODULE-IDENTITY, NOTIFICATION-TYPE, Integer32,Counter32,Unsigned32
        	FROM SNMPv2-SMI
		DisplayString,
		TimeStamp
			FROM SNMPv2-TC
    	rcftChassisIndex, rcftSlotIndex,rcftMibObjects
       	FROM RAISECOM-RCFT-MIB;

	 rcftRemoteDeviceMib MODULE-IDENTITY
	    LAST-UPDATED "1203021725Z"
	    ORGANIZATION "RaiseCom Technology CO.,LTD"
	    CONTACT-INFO
	        "
	       www.raisecom.com
	        "
	    DESCRIPTION
	        "MIB for RC002 Remote Device equipment."
	    REVISION      "0507040000Z"
	    DESCRIPTION
	        ""
        REVISION      "0901090000Z"
        DESCRIPTION
              "
                rcftRemoteE1PortStatus add defination for BIT19;
                rcftRemoteDeviceStatus add defination for BIT10-BIT16;
                add node:rcftRemoteDeviceApsWaitToRestore;
                add trap:rcftRemoteDevSPChannelTrap,rcftRemoteDevPSChannelTrap;
		in rcftRemoteE1Balance:replace (2)unbalance by (2)imbalance
				--by sunying"
        REVISION      "0901210000Z"
        DESCRIPTION
              "
                add node:rcftRemoteDeviceProductType,rcftRemoteDeviceProtocolVer,rcftRemoteDeviceVenderCode;
                rcftRemoteEthFxPortStatus增加对bit5-bit7的定义;
                rcftRemoteEthFxOrder增加枚举24;
				--by sunying"
        REVISION      "0902090000Z"
        DESCRIPTION
              "
                add node:rcftRemoteDeviceModelID;
                rcftRemoteDeviceStatus增加对bit17的定义;
				--by sunying"
        REVISION      "0903170000Z"
        DESCRIPTION
              "
                rcftRemoteEthFxPortStatus 增加对bit8的定义;
				--by sunying"
       REVISION      "0903240000Z"
       DESCRIPTION
              "
                add node:rcftRemoteDeviceApsE6SwitchDelay,rcftRemoteDeviceApsE3SwitchDelay
				--by sunying"

	   REVISION      "0904150000Z"
       DESCRIPTION
              "
                rcftRemoteDeviceOrder add enum:
                pdhPortOutsideLoopEnable(17),   将 DESCRIPTION中用到的但是枚举没有列出来的情况补上.
                StatisticInfoClear(24),统计信息清零
                defaultConfigDate(25),	新增恢复出厂默认配置命令
				--by kuanglili"
	   REVISION      "0905140000Z"
       DESCRIPTION
              "
                rcftRemoteV35PortAlarmStatus 增加对bit12的定义;
				--by wu yanxiong"
	  REVISION      "0905150000Z"
      DESCRIPTION
              "
                rcftRemoteDeviceOrder add enum:
                portOutsideLoopEnable(17),   上次命名重复.
                rcftRemoteE1PortStatus:增加bit20/21位定义
				--by kuanglili"
	  REVISION      "0905190000Z"
      DESCRIPTION
              "
                rcftRemoteEthFxModuleType 和 rcftRemotePdhPortModuleType 中取消了ss3(9) 光头类型
                采用公司统一的光头类型(即ss34(9) 、ss35(10))
				--by kuanglili"
	  REVISION      "0905260000Z"
      DESCRIPTION
              "
				增加了rcftRemoteV35PortDSRTrap;
				--by wuyanxiong"
	  REVISION      "0905260000Z"
      DESCRIPTION
              "
                添加RC906G-FE/X-4E1-REMOTE、RC906-FE/X-E1-REMOTE设备类型
				--by kuanglili"

 	   REVISION      "0905271600Z"
       DESCRIPTION
              "
				add rcftRemoteEthFxPortSFPType;
				--by xujingru"
	  REVISION      "0906091600Z"
       DESCRIPTION
              "
				add rcftRemoteDeviceVLANTagDirection、rcftRemoteDeviceVLANTagModule、rcftRemoteDeviceISPTPID
				rcftRemoteEthFxPortSFPInfo  、rcftRemoteEthFxPortLoopStatus、rcftRemoteEthFxPortInputSignalLosTrap;
				--by kuanglili"
   	   REVISION      "0907021600Z"
       DESCRIPTION
              "
				rcftRemoteVideoPortStatus 增加双向视频口的特性 BIT3-BIT7
				add rcftRemoteVideoPortSignalInLos视频输入信号丢失告警
				    rcftRemoteVideoPortSignalOutLos视频输出信号丢失告警
				--by wu yanxiong"
   	   REVISION      "0907171600Z"
       DESCRIPTION
              "
				添加rcftRemoteE1DS1PortType,用以在ifTable入库等情况下在E1表中
				区分E1和DS1接口类型。
				--by wu yanxiong"
   	   REVISION      "0908190000Z"
       DESCRIPTION
              "
				1、把rcftRemoteE1DS1PortType移置设备级；
				2、添加设备级mib节点rcftRemoteDeviceE1FrameChannel、rcftRemoteDeviceManageID；
				3、添加远端E1接口级mib节点 rcftRemoteE1CVCnt；
				4、修改rcftRemoteEthFeTxRestrictSpeed 注释 为发送带宽
				5、添加rcftRemoteE1PortStatus BIT22 网管通道模式 位
				6、添加rcftRemoteE1ClockMode 枚举值 3：透传   4：E1接收
				7、rcftRemoteE1BertStatus 属性 read-write
				8、增加rcftRemoteEthFxPortStatus bit9: 光口的位置属性。
				--by wu yanxiong"

	  REVISION      "0908211600Z"
     DESCRIPTION
              "
				add rcftRemoteEthFxPortRxRestrictSpeed、rcftRemoteEthFxPortTxRestrictSpeed、
				rcftRemoteEthFxSFPDiagnoWarningStatus 和相应的预警;
				--by kuanglili"

	  REVISION      "0909021000Z"
     DESCRIPTION
              "
       add device type:
               rcftTypeRC521H-FE-DoubleFiber-S(20073),   --双纤台式
               rcftTypeRC521H-FE-SingleFiber-S(20074),   --单纤台式
				--by xujingru
              "

	  REVISION      "0909081430Z"
     DESCRIPTION
              "
       add device type:
               rcftTypeRC521H-FE-S(20075),
				--by xujingru
              "
	REVISION      "0909091130Z"
     DESCRIPTION
              "
            add device type:
               rcftTypeRCMS2802-60FX-SLAVE-REV-A(22084),
				--by kuanglili
              "
	REVISION      "0909091630Z"
     DESCRIPTION
              "
            去掉 rcftRemoteEthFxPortStatus bit9: 光口的位置属性。
            改为独立节点 rcftRemoteEthFxPortLineOrClient
				--by wuyanxiong
              "
 	REVISION      "0909180000Z"
     DESCRIPTION
              "
				增加64位 流量统计节点
				rcftRemoteEthFx64RxBytes	Counter64
				rcftRemoteEthFx64TxBytes	Counter64
				 --by wuyanxiong
			  "
 	REVISION      "0909270000Z"
     DESCRIPTION
              "
				rcftRemoteEthFxModuleType 和 rcftRemotePdhPortModuleType 中
				增加了SFP(15) 光头类型，按照公司统一的光头类型
					 --by wuyanxiong
			  "

	  REVISION      "0910301006Z"
      DESCRIPTION
              "
				增加64位 rcftRemoteEthFxCOS
					 --by kuanglili
			  "
        REVISION      "0912210000Z"
        DESCRIPTION
              "
				根据RCVS1000-501BL等设备的mib编程说明及代码，断定
				rcftRemoteVideoPortStatus bit 0 原枚举值有误，更正为
				0：正常；1：告警

									--by wuyanxiong
			  "
        REVISION      "1003030000Z"
        DESCRIPTION
              "
				add remote device
				rcftRemoteDeviceMibUse
					--by wuyanxiong
			  "
        REVISION      "1003040000Z"
        DESCRIPTION
              "
				add device type:
				rcftTypeRC552-FE-REV-B(21007),
					--by wuyanxiong
			  "
        REVISION      "1003100000Z"
        DESCRIPTION
              "
				修改rcftRemoteDeviceMibUse枚举值，从1开始
		      	{
		      		mib002(1),
		      		rccomlib(2)
		      	}
					--by wuyanxiong
			  "
		REVISION      "1009290950Z"
        DESCRIPTION
              "
				add subcard moudle type:
				e-SUBM-2E1-A,
				--by yangbintao
			   "
		REVISION      "1010221657Z"
        DESCRIPTION
              "
              添加远端配置信息表rcftRemoteEthFePortConfTable,用于配置信息的显示和配置
              其中添加配置信息表入口rcftRemoteEthFePortConfEntry,同时定义两个节点：
              rcftRemoteEthFeConfSpeed
			  rcftRemoteEthFeConfDuplex

			  --by yangbintao
			   "
		REVISION      "1011150000Z"
        DESCRIPTION
              "
				1、add subcard moudle type:
					rcftTypeRCMS2902-120LFE-REMOTE(62589),   ---对应设备类型0xF47D
					rcftTypeRCMS2902-240LFE-REMOTE(62592),   ---对应设备类型0xF480
					rcftTypeRCMS2902-60FE-REMOTE(62595),      ---对应设备类型0xF483
					rcftTypeRC862-60-REMOTE(62598),    		 ---对应设备类型0xF486
					rcftTypeRC862-30-REMOTE(62603),    		 ---对应设备类型0xF48B
					rcftTypeRCMS2911-480FE(62607),    		---对应设备类型0xF48F
					rcftTypeRCMS2912-480FE-REMOTE(62611),    ---对应设备类型0xF493
					rcftTypeRCMS2912-240FE-REMOTE(62615),    ---对应设备类型0xF497
					rcftTypeRCMS2901-480EFE(62616),    		---对应设备类型0xF498
					rcftTypeRC861-480E(62618),	            ---对应设备类型0xF49A

				2、修改设备名称RCMS2912-8/4T1E1GE 改为 RCMS2912-8/4E1T1GE

						--by wuyanxiong
			   "

		REVISION      "1112191725Z"
        DESCRIPTION
              "
				add rcftRemoteDeviceStatus 18 and 19 enum
						--by yangbintao
			   "
		REVISION      "1203020000Z"
        DESCRIPTION
              "
				1、rcftRemoteMoudleV35Status 定义BIT8-BIT11;

			  			--by wuyanxiong
			  "



	    ::= { rcftMibObjects 6 }

     --对象定义
     	rcftRemoteDeviceSystemMIB  OBJECT IDENTIFIER ::= { rcftRemoteDeviceMib 1 }
    	rcftRemoteDeviceSysObjects OBJECT IDENTIFIER ::= { rcftRemoteDeviceSystemMIB 1 }
    	rcftRemoteDeviceSysTraps   OBJECT IDENTIFIER	::={ rcftRemoteDeviceSystemMIB 2}

      	rcftRemoteDeviceEthMIB     OBJECT IDENTIFIER ::= { rcftRemoteDeviceMib 2 }
      	rcftRemoteDeviceEthFeMIB		OBJECT IDENTIFIER ::= {rcftRemoteDeviceEthMIB 1}
      	rcftRemoteDeviceEthFeObjects	OBJECT IDENTIFIER ::={rcftRemoteDeviceEthFeMIB 1}
      	rcftRemoteDeviceEthFeTraps		OBJECT IDENTIFIER ::={rcftRemoteDeviceEthFeMIB 2}

      	rcftRemoteDeviceEthFxMIB		OBJECT IDENTIFIER ::= {rcftRemoteDeviceEthMIB 2}
      	rcftRemoteDeviceEthFxObjects	OBJECT IDENTIFIER ::={rcftRemoteDeviceEthFxMIB 1}
      	rcftRemoteDeviceEthFxTraps		OBJECT IDENTIFIER ::={rcftRemoteDeviceEthFxMIB 2}
      	rcftRemoteDeviceEthFxPerformance	OBJECT IDENTIFIER ::={rcftRemoteDeviceEthFxMIB 3}

      	rcftRemoteDeviceE1MIB       OBJECT IDENTIFIER ::= { rcftRemoteDeviceMib 3 }
      	rcftRemoteDeviceE1Objects	OBJECT IDENTIFIER	::={rcftRemoteDeviceE1MIB 1}
      	rcftRemoteDeviceE1Traps		OBJECT IDENTIFIER	::={rcftRemoteDeviceE1MIB 2}

      	rcftRemoteDeviceSHDSLMIB       	OBJECT IDENTIFIER ::= { rcftRemoteDeviceMib 4 }
      	rcftRemoteSHDSLPortObjects		OBJECT IDENTIFIER	::={rcftRemoteDeviceSHDSLMIB 1}
      	rcftRemoteSHDSLPortPerformance  OBJECT IDENTIFIER	::={rcftRemoteDeviceSHDSLMIB 2}
      	rcftRemoteSHDSLPortTraps		OBJECT IDENTIFIER	::={rcftRemoteDeviceSHDSLMIB 10}

      	rcftRemoteDeviceV35MIB       	OBJECT IDENTIFIER ::= { rcftRemoteDeviceMib 5 }
      	rcftRemoteV35PortObjects		OBJECT IDENTIFIER	::={rcftRemoteDeviceV35MIB 1}
      	rcftRemoteV35PortPerformance  OBJECT IDENTIFIER	::={rcftRemoteDeviceV35MIB 2}
      	rcftRemoteV35PortTraps		OBJECT IDENTIFIER	::={rcftRemoteDeviceV35MIB 3}

	   --------------------------DS3 E3端口------------------------------------
    	rcftRemoteDS3E3PortMIB OBJECT IDENTIFIER	 ::= {rcftRemoteDeviceMib 6}
	    rcftRemoteDS3E3PortObjects  OBJECT IDENTIFIER	 ::= {rcftRemoteDS3E3PortMIB 1}
	    rcftRemoteDS3E3PortPerformance OBJECT IDENTIFIER	 ::= {rcftRemoteDS3E3PortMIB 2}
	    rcftRemoteDS3E3PortTraps OBJECT IDENTIFIER	 ::= {rcftRemoteDS3E3PortMIB 10}

	   --------------------------pdh端口------------------------------------
    	rcftRemotePdhPortMIB OBJECT IDENTIFIER	 ::= {rcftRemoteDeviceMib 7}
	    rcftRemotePdhPortObjects  OBJECT IDENTIFIER	 ::= {rcftRemotePdhPortMIB 1}
	    rcftRemotePdhPortPerformance OBJECT IDENTIFIER	 ::= {rcftRemotePdhPortMIB 2}
	    rcftRemotePdhPortTraps OBJECT IDENTIFIER	 ::= {rcftRemotePdhPortMIB 10}

	    --------------------------DS1端口------------------------------------
    	rcftRemoteDS1PortMIB OBJECT IDENTIFIER	 ::= {rcftRemoteDeviceMib 8}
	    rcftRemoteDS1PortObjects  OBJECT IDENTIFIER	 ::= {rcftRemoteDS1PortMIB 1}
	    rcftRemoteDS1PortPerformance OBJECT IDENTIFIER	 ::= {rcftRemoteDS1PortMIB 2}
	    rcftRemoteDS1PortTraps OBJECT IDENTIFIER  ::= {rcftRemoteDS1PortMIB 10}

 	    --------------------------子卡------------------------------------
    	rcftRemoteMoudleMIB OBJECT IDENTIFIER	 ::= {rcftRemoteDeviceMib 9}
    	rcftRemoteMoudle OBJECT IDENTIFIER	 ::= {rcftRemoteMoudleMIB 1}
    	rcftRemoteMoudleObjects  OBJECT IDENTIFIER	 ::= {rcftRemoteMoudle 1}
    	rcftRemoteMoudleTraps OBJECT IDENTIFIER	 ::= {rcftRemoteMoudle 10}

   		rcftRemoteMoudleEthFe OBJECT IDENTIFIER	 ::= {rcftRemoteMoudleMIB 2}
   	 	rcftRemoteMoudleEthFeObjects  OBJECT IDENTIFIER	 ::= {rcftRemoteMoudleEthFe 1}
    	rcftRemoteMoudleEthFePerformance OBJECT IDENTIFIER	 ::= {rcftRemoteMoudleEthFe 2}
    	rcftRemoteMoudleEthFeTraps OBJECT IDENTIFIER	 ::= {rcftRemoteMoudleEthFe 10}

    	rcftRemoteMoudlePdh OBJECT IDENTIFIER	 ::= {rcftRemoteMoudleMIB 3}
   		rcftRemoteMoudlePdhObjects  OBJECT IDENTIFIER	 ::= {rcftRemoteMoudlePdh 1}
    	rcftRemoteMoudlePdhTraps OBJECT IDENTIFIER	 ::= {rcftRemoteMoudlePdh 10}

    	rcftRemoteMoudleE1  OBJECT IDENTIFIER	 ::= {rcftRemoteMoudleMIB 4}
    	rcftRemoteMoudleE1Objects  OBJECT IDENTIFIER	 ::= {rcftRemoteMoudleE1 1}
    	rcftRemoteMoudleE1Performance OBJECT IDENTIFIER	 ::= {rcftRemoteMoudleE1 2}
    	rcftRemoteMoudleE1Traps OBJECT IDENTIFIER	 ::= {rcftRemoteMoudleE1 10}

    	rcftRemoteMoudleV35 OBJECT IDENTIFIER	 ::= {rcftRemoteMoudleMIB 5}
    	rcftRemoteMoudleV35Objects  OBJECT IDENTIFIER	 ::= {rcftRemoteMoudleV35 1}
    	rcftRemoteMoudleV35Traps OBJECT IDENTIFIER	 ::= {rcftRemoteMoudleV35 10}


  		 --------------------------AUDIO端口------------------------------------
       	rcftRemoteAudioPortMIB OBJECT IDENTIFIER	 ::= {rcftRemoteDeviceMib 10}
	    rcftRemoteAudioPortObjects  OBJECT IDENTIFIER	 ::= {rcftRemoteAudioPortMIB 1}
	    rcftRemoteAudioPortPerformance OBJECT IDENTIFIER	 ::= {rcftRemoteAudioPortMIB 2}
	    rcftRemoteAudioPortTraps OBJECT IDENTIFIER  ::= {rcftRemoteAudioPortMIB 10}

	    -----------------------Video 视频口--------------------------------
	    rcftRemoteVideoPortMIB OBJECT IDENTIFIER	 ::= {rcftRemoteDeviceMib 11}
	    rcftRemoteVideoPortObjects  OBJECT IDENTIFIER	 ::= {rcftRemoteVideoPortMIB 1}
	    rcftRemoteVideoPortPerformance OBJECT IDENTIFIER	 ::= {rcftRemoteVideoPortMIB 2}
	    rcftRemoteVideoPortTraps OBJECT IDENTIFIER  ::= {rcftRemoteVideoPortMIB 10}

   	 	----------------------Data 数据口---------------------------------
   	 	rcftRemoteDataPortMIB OBJECT IDENTIFIER	 ::= {rcftRemoteDeviceMib 12}
	    rcftRemoteDataPortObjects  OBJECT IDENTIFIER	 ::= {rcftRemoteDataPortMIB 1}
	    rcftRemoteDataPortPerformance OBJECT IDENTIFIER	 ::= {rcftRemoteDataPortMIB 2}
	    rcftRemoteDataPortTraps OBJECT IDENTIFIER  ::= {rcftRemoteDataPortMIB 10}

    		----------------------SimpleModule数据口---------------------------------
   	 	rcftRemoteSimpleModuleMIB OBJECT IDENTIFIER	 ::= {rcftRemoteDeviceMib 13}
	    rcftRemoteSimpleModuleObjects  OBJECT IDENTIFIER	 ::= {rcftRemoteSimpleModuleMIB 1}
	    rcftRemoteSimpleModulePerformance OBJECT IDENTIFIER	 ::= {rcftRemoteSimpleModuleMIB 2}
	    rcftRemoteSimpleModuleTraps OBJECT IDENTIFIER  ::= {rcftRemoteSimpleModuleMIB 10}

	    -------------------VLAN MIB----------------------------------------
	    rcftRemoteVLANMIB	  OBJECT IDENTIFIER ::= { rcftRemoteDeviceMib 14 }
	    rcftRemoteVLANObjects	OBJECT IDENTIFIER ::= {rcftRemoteVLANMIB 1}

	    ---------------------- FPGA 或交换芯片 流量统计 ----------------------
	    rcftRemotePerformaceMib	OBJECT IDENTIFIER ::={rcftRemoteDeviceMib 15}
    	rcftRemoteStatisticPerformance OBJECT IDENTIFIER ::={rcftRemotePerformaceMib 1}

    ----------------------VCG MIB-------------------------
    	rcftRemoteVCGMib		OBJECT IDENTIFIER ::={rcftRemoteDeviceMib 16}

    	rcftRemoteVCGObjects  OBJECT IDENTIFIER ::={rcftRemoteVCGMib 1}
    	rcftRemoteVCGPerformance OBJECT IDENTIFIER ::={rcftRemoteVCGMib 2}
    	rcftRemoteVCGTraps OBJECT IDENTIFIER ::={rcftRemoteVCGMib 10}



 -- 系统配置表
 		rcftRemoteDeviceSysTable OBJECT-TYPE
              SYNTAX  SEQUENCE OF RcftRemoteDeviceSysEntry
              MAX-ACCESS  not-accessible
              STATUS  current
              DESCRIPTION
                 "
                 The Remote Device System table.
                 "
             ::= { rcftRemoteDeviceSysObjects 1 }

    	rcftRemoteDeviceSysEntry OBJECT-TYPE
              SYNTAX  RcftRemoteDeviceSysEntry
              MAX-ACCESS  not-accessible
              STATUS  current
              DESCRIPTION
                 "
                 An entry in the rc952 system table.

                 "
              INDEX   { rcftChassisIndex, rcftSlotIndex,rcftRemoteDeviceIndex }
             ::= { rcftRemoteDeviceSysTable 1 }

     	RcftRemoteDeviceSysEntry ::=
              SEQUENCE {
                   rcftRemoteDeviceIndex		 	Integer32,
                   rcftRemoteDeviceExist         	INTEGER,
                   rcftRemoteDeviceType    		 	INTEGER,
                   rcftRemoteDeviceLocalPortType	INTEGER,
                   rcftRemoteDeviceLocalPortIndex	INTEGER,
                   rcftRemoteDeviceVersionInfo	 	OCTET STRING,
                   rcftRemoteSysTemperature      	INTEGER,
                   rcftRemoteSysVoltageStatus      	INTEGER,
                   rcftRemoteDeviceWorkMode			INTEGER,
                   rcftRemoteDeviceFrameLen			INTEGER,
                   rcftRemoteDeviceOrder			INTEGER,
                   rcftRemoteDeviceConfigFlag		INTEGER,
                   rcftRemoteSlotAutoCutErrLineEn   INTEGER,
                   rcftRemotePowerSupply			INTEGER,
                   rcftRemoteDevicePowerDown		INTEGER,
                   rcftRemoteDeviceClkMode			INTEGER,
                   rcftRemoteDeviceE1SubCardType	INTEGER,
                   rcftRemoteDeviceGateway			OCTET STRING,
                   rcftRemoteDeviceIP				OCTET STRING,
                   rcftRemoteDeviceSubnetMask		OCTET STRING,
                   rcftRemoteDeviceVLANID			INTEGER,
                   rcftRemoteDeviceCommunityRW		INTEGER,
                   rcftRemoteDeviceCommunityLength	INTEGER,
                   rcftRemoteDeviceCommunity		OCTET STRING,
                   rcftRemoteDeviceVoltageValue		Unsigned32,
                   rcftRemoteDeviceStatus			INTEGER,
                   rcftRemoteSubModuleExist			INTEGER,
                   rcftRemoteMultiE1LoopOrder		OCTET STRING,
                   rcftRemoteOrderTimeParameter		INTEGER,
                   rcftRemoteOrderModeParameter		INTEGER,
                   rcftRemoteSDRAMBuf				INTEGER,
                   rcftRemoteRLPStatus				INTEGER,
                   rcftRemoteLALStatus				INTEGER,
                   rcftRemoteRALStatus				INTEGER,
                   rcftRemoteDeviceSwitchStatus		INTEGER,
                   rcftRemoteDeviceMoudleExist		INTEGER,
                   rcftRemoteCardInformation 		OCTET STRING,
                   rcftRemoteSwitchType		INTEGER,
                   rcftRemoteConnectMode	INTEGER,
                   rcftRemoteQosEnable		INTEGER,
                   rcftRemoteBaseCOS		INTEGER,
                   rcftRemoteDSCP		OCTET STRING,
                   rcftRemoteQueuesPolicy 	INTEGER,
                   rcftRemoteMultiE1AlarmRejectOrder  OCTET STRING,
                   rcftRemoteT1PortPulseWaveForm  INTEGER,
                   rcftRemoteT1PortCodeType	INTEGER,
                   rcftRemoteDeviceSabitMode		INTEGER,
                   rcftRemoteDeviceApsWaitToRestore INTEGER,
                   rcftRemoteDeviceCLKChannel	INTEGER,
                   rcftRemoteDeviceRmcChannelType	INTEGER,
                   rcftRemoteDeviceProductType	OCTET STRING,
                   rcftRemoteDeviceProtocolVer	INTEGER,
                   rcftRemoteDeviceVenderCode	INTEGER,
                   rcftRemoteDeviceModelID	INTEGER,
                   rcftRemoteE1PortNumber  INTEGER,
                   rcftRemoteDeviceVLANType	INTEGER,
                   rcftRemoteDeviceQoSPolicy	INTEGER,
                   rcftRemoteDeviceApsE3SwitchDelay  INTEGER,
                   rcftRemoteDeviceApsE6SwitchDelay  INTEGER,
                   rcftRemoteDeviceVLANTagDirection	 INTEGER,
                   rcftRemoteDeviceVLANTagModule	INTEGER,
                   rcftRemoteDeviceISPTPID		INTEGER,
                   rcftRemoteE1DS1PortType		INTEGER,
                   rcftRemoteDeviceE1FrameChannel	INTEGER,
                   rcftRemoteDeviceManageID		INTEGER,
                   rcftRemoteDeviceMibUse		INTEGER

                   }


        rcftRemoteDeviceIndex OBJECT-TYPE
           SYNTAX      Integer32
           MAX-ACCESS  read-only
           STATUS      current
           DESCRIPTION
           "
          	远端设备的索引
           "
        	::= { rcftRemoteDeviceSysEntry 1 }

 		rcftRemoteDeviceExist OBJECT-TYPE
            SYNTAX      INTEGER
            {
          	  exist(1),
          	  noexist(2)
            }
           MAX-ACCESS  read-only
           STATUS      current
           DESCRIPTION
           "
          	远端设备是否在位
           "
           ::= { rcftRemoteDeviceSysEntry 2 }

        rcftRemoteDeviceType   OBJECT-TYPE
           SYNTAX      INTEGER
           {
               rcftTypeRCMS2802-240GE-REV-A-REMOTE(5394),   -- RC006设备，只能做rc002的一级远端，RCMS2802-120/240LGE-BL(B)作为局端
               rcftTypeRC501-FE-REV-C(20001),
               rcftTypeRC601-FE-REV-C(20002),
               rcftTypeRC511-FE-REV-A(20003),
               rcftTypeRC952-FEE1-REV-A(20004),
               rcftTypeRC952-FXE1-REV-A(20005),
               rcftTypeRC601-FE-REV-E(20006),
               rcftTypeRC511-4FE-REV-A(20007),
               rcftTypeRC511-FE-C-REV-A(20008),
               rcftTypeRC951-FEE1-REV-A(20009),
               rcftTypeRC513-FE-REV-A(20010),
               rcftTypeRC513-FE-C-REV-A(20011),
               rcftTypeRC954-FE4E1-REV-A(20012),
               rcftTypeRC954-FX4E1-REV-A(20013),
               rcftTypeRC953-FE4E1-REV-A(20014),
               rcftTypeRC953-FX4E1-REV-A(20015),
               rcftTypeRC953-FE8E1-REV-A(20016),
               rcftTypeRC953-FX8E1-REV-A(20017),
               rcftTypeRC953-FE8E1-BL-REV-A(20018),
               rcftTypeRC953-FX8E1-BL-REV-A(20019),
               rcftTypeRC532-FE-REV-A(20020),
               rcftTypeRC531-FE-REV-A(20021),
               rcftTypeRC532-2FE-REV-A(20022),
               rcftTypeRC1102-E1-SLAVE-REV-B1(20023),	--增加了性能统计的新协议
               rcftTypeRC1102-E1-SLAVE-BL-REV-A1(20024),--增加了性能统计的新协议
               rcftTypeRC954-2FE4E1-BL-REV-A(20025),
               rcftTypeRC954-FE4E1-BL-REV-A(20026),
               rcftTypeRC954-FX4E1-BL-REV-A(20027),
               rcftTypeRC954-2FE8E1-BL-REV-A(20028),
               rcftTypeRC1102-V35-REV-A1(20029), 	---增加了误码测试和性能统计
               rcftTypeRC1102-V35-REV-B(20030),    ---增加v35接收时钟自适应和v35速率配置
               rcftTypeRC602-GEF-REV-B(20031),		--光口用sfp
               rcftTypeRC802-DS3E3-REV-A(20032),
               rcftTypeE-SUBM-FE4E1-A(20033),
               rcftTypeRC954-FE8E1-REV-A(20034),
               rcftTypeRC1102-E1-REV-B2(20035),  --增加了误码测试的新协议
               rcftTypeRC1102-E1-BL-REV-A2(20036),    --增加了误码测试的新协议
               rcftTypeRC952-FE-DS3E3-REV-A-SLAVE(20037),
               rcftTypeRC802-DS1-REV-A-SLAVE(20038),
               rcftTypeRC952-FE-DS1-REV-A-SLAVE(20039),
               rcftTypeRC952-FE-DS3E3-F-REV-A-SLAVE(20040),------增加了DS3E3成帧、线路编码、传输距离
               rcftTypeRC852-30-SLAVE-REV-B(20041),
               rcftTypeRC951-4FEE1-REV-A(20042),


               rcftTypeRC512-FE-REV-A-SLAVE-M(20043),
               rcftTypeRC512-FE-REV-A-SLAVE-S1(20044),
               rcftTypeRC512-FE-REV-A-SLAVE-S2(20045),
               rcftTypeRC512-FE-REV-A-SLAVE-S3(20046),

               rcftTypeRC512-FE-REV-A-SLAVE-noOptical(20047),       ------拨码到这里时，显示光口类型为空

               rcftTypeRC512-FE-REV-A-SLAVE-SS13(20048),
               rcftTypeRC512-FE-REV-A-SLAVE-SS23(20049),
               rcftTypeRC512-FE-REV-A-SLAVE-SS34(20050),

               rcftTypeRC512-FE-REV-A-S-M(20051),
               rcftTypeRC512-FE-REV-A-S-S1(20052),
               rcftTypeRC512-FE-REV-A-S-S2(20053),
               rcftTypeRC512-FE-REV-A-S-S3(20054),

               rcftTypeRC512-FE-REV-A-S-noOptical(20055),
               rcftTypeRC512-FE-REV-A-S-SS13(20056),
               rcftTypeRC512-FE-REV-A-S-SS23(20057),
               rcftTypeRC512-FE-REV-A-S-SS34(20058),    ------当前不支持

               rcftTypeRC512-FE-REV-A-C-M(20059),
               rcftTypeRC512-FE-REV-A-C-S1(20060),
               rcftTypeRC512-FE-REV-A-C-S2(20061),
               rcftTypeRC512-FE-REV-A-C-S3(20062),

               rcftTypeRC512-FE-REV-A-C-noOptical(20063),  ------拨码到这里时，显示光口类型为空
               rcftTypeRC512-FE-REV-A-C-SS13(20064),
               rcftTypeRC512-FE-REV-A-C-SS23(20065),
               rcftTypeRC512-FE-REV-A-C-SS34(20066),
               rcftTypeRC952-FXE1-REV-C-SLAVE(20067),
               rcftTypeRC511-4FE-REV-B-SLAVE(20068),

               rcftTypeRC952-FEE1-REV-B-REMOTE(20069),  --对应硬件b版的移动模式 ，硬件b版的其他模式同a版
               rcftTypeRC906H-FEE1-REMOTE-PRIVATE(20070),

               rcftTypeRC521H-FE-DoubleFiber-S(20073),   --双纤台式
               rcftTypeRC521H-FE-SingleFiber-S(20074),   --单纤台式
               rcftTypeRC521H-FE-S(20075),
               rcftTypeRC522E-FE-REMOTE(20076),
               rcftTypeRC521E-FE(20077),
               rcftTypeRC512-FE(20078),  --对于B版以前未处理的光头类型统一占用的类型号，虚拟的号
               rcftTypeRC512-FE-SLAVE(20079),  --对于B版以前未处理的光头类型统一占用的类型号，虚拟的号

               rcftTypeRC551-FE-REV-A(21001),
               rcftTypeRC551-GE-REV-A(21002),
               rcftTypeRC551-4FE-REV-A(21003),
               rcftTypeRC551-GE-REV-A1(21004), ---和RC551-GE-REV-A相比，增加了SFP数字诊断相关的管理对象
               rcftTypeRC552-GE-REV-C(21005),
               rcftTypeRC954-FX8E1-REV-A(21006),
               rcftTypeRC552-FE-REV-B(21007),

               rcftTypeRC831-120-REV-A(22050),         ---22000字段的为7017设备
               rcftTypeRC831-240-REV-A(22051),
               rcftTypeRC831-240E-REV-A(22052),
               rcftTypeRC831-30-FV35-REV-A(22053),
               rcftTypeRC831-60-FV35-REV-A(22054),
               rcftTypeRC832-30-SLAVE-REV-A(22055),
               rcftTypeRC832-30-FV35-SLAVE-REV-A(22056),
               rcftTypeRC832-60-SLAVE-REV-A(22057),
               rcftTypeRC832-120L-SLAVE-REV-A(22058),
               rcftTypeRC832-240L-SLAVE-REV-A(22059),
               rcftTypeRCMS2801-30FE-FV35-REV-A(22060),
               rcftTypeRCMS2801-60FE-FV35-REV-A(22061),
               rcftTypeRCMS2801-120FE-SLAVE-REV-A(22062),
               rcftTypeRCMS2801-240FE-SLAVE-REV-A(22063),
               rcftTypeRCMS2801-240EFE-SLAVE-REV-A(22064),
               rcftTypeRCMS2802-30FE-SLAVE-REV-A(22065),
               rcftTypeRCMS2802-60FE-SLAVE-REV-A(22066),
               rcftTypeRCMS2802-120LFE-SLAVE-REV-A(22070),
               rcftTypeRCMS2802-240LFE-SLAVE-REV-A(22071),
               rcftTypeRC832-30-FV35-SLAVE-REVB(22072),
               rcftTypeRC804-30B-S1-SLAVE-REV-A(22073),
               rcftTypeRC806-30B-S1-SLAVE-REV-A(22074),
               rcftTypeRC832-30-FV35-SLAVE-REVA1(22075),
               rcftTypeRC831-30-FV35-SLAVE-REVA1(22076),
               rcftTypeRC831-60-FV35-SLAVE-REVA1(22077),
               rcftTypeRCMS2801-30FE-FV35-SLAVE-REVA1(22078),
               rcftTypeRCMS2801-60FE-FV35-SLAVE-REVA1(22079),
               rcftTypeRCMS2802-2T1-FE-SLAVE-REV-A(22081),
               rcftTypeRCMS2802-4T1-FE-SLAVE-REV-A(22082),
               rcftTypeRCMS2802-8T1-FE-SLAVE-REV-A(22083),
               rcftTypeRCMS2802-60FX-SLAVE-REV-A(22084),

               rcftTypeRC1101-FEV35E1-REV-A(25004),    --从25000开始是遵循通信约定4的远端板卡类型定义
               rcftTypeRC1102-FE-REV-B-SLAVE(25005),
               rcftTypeRC1102-FE-4W-REV-A-SLAVE(25006),
               rcftTypeRC1101-FE-V35E1-REV-B(25007),


               rcftTypeRCMS2802-120LGE-BL-A-SLAVE(26008),    --约定4的光端机
               rcftTypeRCMS2802-240LGE-BL-A-SLAVE(26011),
               rcftTypeRCMS2802-60GE-BL-A-SLAVE(26099),
               rcftTypeRCMS2802-30GE-BL-A-SLAVE(26100),

               rcftTypeRC906H-FEE1-REV-A-REMOTE(45313),   ---对应设备类型0xB101, 管理对象同 RC952-FEE1-REV-B
               rcftTypeRC906H-FXE1-REV-A-REMOTE(45314),   ---对应设备类型0xB102，管理对象同 RC952-FXE1-REV-C

               rcftTypeRC602-GEF-REV-C(45318),		---对应设备类型0xB104

               rcftTypeRC904-PE1-REMOTE(62514),   ---对应设备类型0xf432
               rcftTypeTHIRD-PARTY-PRODUCT(62128),   ---对应设备类型0xf2B0,采用移动标准的第3方产品

               rcftTypeRCMS2802-60GE-BL-REV-B-REMOTE(62471),   ---对应设备类型0xf407
               rcftTypeRCMS2802-120LGE-BL-REV-B-REMOTE(62518),   ---对应设备类型0xf436
               rcftTypeRCMS2802-240LGE-BL-REV-B-REMOTE(62521),   ---对应设备类型0xf439

			   rcftTypeRC958-FE4E1-REV-A-REMOTE(62526),   ---对应设备类型0xF43E
			   rcftTypeRC958-FE8E1-REV-A-REMOTE(62529),   ---对应设备类型0xF441
               rcftTypeRC958-FX4E1-REV-A-REMOTE(62533),   ---对应设备类型0xF445
			   rcftTypeRC958-FX8E1-REV-A-REMOTE(62536),   ---对应设备类型0xF448
			   rcftTypeRC958-FEE1-REV-A-REMOTE(62543),   ---对应设备类型0xF445
			   rcftTypeRC958-FXE1-REV-A-REMOTE(62546),   ---对应设备类型0xF448

			   rcftTypeRC906G-FE4E1-REMOTE(62550),		---对应设备类型0xF456
			   rcftTypeRC906G-FX4E1-REMOTE(62553),		---对应设备类型0xF459
			   rcftTypeRC906G-FEE1-REMOTE(62557),		---对应设备类型0xF45D
			   rcftTypeRC906G-FXE1-REMOTE(62560),		---对应设备类型0xF460
			   rcftTypeRC906G-FE8E1-REMOTE(62563),		---对应设备类型0xF463
			   rcftTypeRC906G-FX8E1-REMOTE(62567),		---对应设备类型0xF467

               rcftTypeRC908-FEV35-REV-A-REMOTE(62540),	  ---对应设备类型0xf44c
               rcftTypeRCVS1000-901UL-REMOTE(62571),	---对应设备类型0xF46B
               rcftTypeRCMS2912-4E1T1GE-REV-A(62575),   ---对应设备类型0xF46F
               rcftTypeRCMS2912-8E1T1GE-REV-A(62578),   ---对应设备类型0xF472

               rcftTypeRCMS2902-120LFE-REMOTE(62589),   ---对应设备类型0xF47D
               rcftTypeRCMS2902-240LFE-REMOTE(62592),   ---对应设备类型0xF480
               rcftTypeRCMS2902-60FE-REMOTE(62595),      ---对应设备类型0xF483
               rcftTypeRC862-60-REMOTE(62598),    		 ---对应设备类型0xF486
               rcftTypeRC862-30-REMOTE(62603),    		 ---对应设备类型0xF48B
               rcftTypeRCMS2911-480FE(62607),    		---对应设备类型0xF48F
               rcftTypeRCMS2912-480FE-REMOTE(62611),    ---对应设备类型0xF493
               rcftTypeRCMS2912-240FE-REMOTE(62615),    ---对应设备类型0xF497
               rcftTypeRCMS2901-480EFE(62616),    		---对应设备类型0xF498
               rcftTypeRC861-480E(62618),	            ---对应设备类型0xF49A

               rcftTypeRCVS1000-501B(206918),		---对应设备类型0x1b06
               rcftTypeRCVS1000-502B(206919),     ---对应设备类型0x1b07
               rcftTypeRCVS1000-504A(206915),     ---对应设备类型0x1b03
               rcftTypeTS1000-UNCONFIG-PRODUCT(64769),      ---对应设备类型0xFD01
               rcftTypeRC521-FE-REV-C(64770),	---对应设备类型0xFD02
               rcftTypeRC521-FE-REV-D(64771),	---对应设备类型0xFD03

               rcftTypeRC952-SE1M-REMOTE(62582),       ---对应设备类型0xF476
               rcftTypeRC952-CSE1M-REMOTE(62606),       ---对应设备类型0xF48E


           }
           MAX-ACCESS  read-only
           STATUS      current
           DESCRIPTION
           "
          	远端设备的类型
          	设备类型号的枚举值21000到22000的属于OAM的设备。
          	22000字段的为7017设备。
          	25000到26000的是收发器模式下的约定四设备；
          	大于26000的是光端机模式下的约定四。
           "
           ::= { rcftRemoteDeviceSysEntry 3 }

       rcftRemoteDeviceLocalPortType	OBJECT-TYPE
           SYNTAX      INTEGER
           {
               ethport(1),
               optical(2),
               e1port(3),
               ghdsl(4)
           }
           MAX-ACCESS  read-only
           STATUS      current
           DESCRIPTION
           "
            远端设备所接局端设备的物理端口类型
          	接口类型（1:电口，2：光口，3：E1口，4:G.口)
           "
           ::= { rcftRemoteDeviceSysEntry 4 }

       rcftRemoteDeviceLocalPortIndex OBJECT-TYPE
           SYNTAX      INTEGER
           MAX-ACCESS  read-only
           STATUS      current
           DESCRIPTION
           "
          	远端设备所接局端设备的物理端口索引，哪一端口被占用相应的位被置1
		   	--------------------------------------------------------------
		    | Bit15 | Bit14 | Bit13 | Bit12 | Bit11 | Bit10 |Bit9 | Bit8 |
		    --------------------------------------------------------------
		    ---------------------------------------------------------
		    | Bit7 | Bit6 | Bit5 | Bit4 | Bit3 | Bit2 | Bit1 | Bit0 |
		    ---------------------------------------------------------

           "
           ::= { rcftRemoteDeviceSysEntry 5 }

       rcftRemoteDeviceVersionInfo  OBJECT-TYPE
          	SYNTAX OCTET STRING(SIZE (0..100))
          	MAX-ACCESS 		read-only
          	STATUS 			current
          	DESCRIPTION
          	"
          	    远端板卡的版本信息版本信息的格式是：A.x-X.x-Ex-Fx.y
                其中：A.x为硬件版本号；X.x为软件版本号；Ex中的x为以太网交换芯片类型；
                Fx.y中的x为FPGA芯片代号，y为FPGA代码版本号。
          	"
            ::= { rcftRemoteDeviceSysEntry 6 }


      rcftRemoteSysTemperature  OBJECT-TYPE
           SYNTAX      INTEGER
           MAX-ACCESS  read-only
           STATUS      current
           DESCRIPTION
           "
          	远端设备温度
           "
           ::= { rcftRemoteDeviceSysEntry 7 }

        rcftRemoteSysVoltageStatus OBJECT-TYPE
           SYNTAX     INTEGER
           {
          		normal(1),
          		toohigh(2),
          		toolow(3)
           }
           MAX-ACCESS  read-only
           STATUS      current
           DESCRIPTION
           "
          	远端设备电压异常
           "
        ::= { rcftRemoteDeviceSysEntry 8 }


        rcftRemoteDeviceWorkMode  OBJECT-TYPE
        	SYNTAX		INTEGER
        	{
        	   masterCtrl(1),
        	   slaveCtrl(2)
        	}
           MAX-ACCESS  read-only
           STATUS      current
           DESCRIPTION
           "
          	远端设备的工作模式(1:主控，2:从控)
           "
        ::= { rcftRemoteDeviceSysEntry 9 }


       rcftRemoteDeviceFrameLen	OBJECT-TYPE
	        SYNTAX INTEGER
	        {
	    	   framelen1916B(1),
	    	   framelen1536B(2),
	           framelen9728B(3),
	    	   framelen1518B(4),
	    	   framelen9kB(5),
	    	   framelen2048(6)
	        }
	        MAX-ACCESS read-write
	        STATUS current
	        DESCRIPTION
	          "
	          	本模块以太网帧的最大帧长：（1：1916B，2：1536B）.
	          	The max frame length of the ethernet port in the remote module.
	          "
             ::= { rcftRemoteDeviceSysEntry 10 }


       rcftRemoteDeviceOrder	OBJECT-TYPE
       		SYNTAX		INTEGER
       		{
       			  reset(1),
       			  reqInfoStart(2),
       			  reqInfoStop(3),
       			  shdslPortReset(4),
       			  shdslPortInisdeLoopEnable(5),
       			  shdslPortOutsideLoopEnable(6),
       			  shdslPortInisdeLoopDisable(7),
       			  shdslPortOutsideLoopDisable(8),
		 		  e1UnUsedAlarmMask(9),
		          e1UnUsedAlarmUnMask(10),
		          pdhPortOutsideLoopEnable(11),
		          ds3E3PortOutsideLoopEnable(12),
		          allLoopDisable(13),
		          errorCodeTestEnable(14),
		          errorCodeTestDisable(15),

		          portOutsideLoopEnable(17),  --kuanglili 20090515 modified: named duplicate
		          statisticInfoClear(24),
		          defaultConfigData(25)
       		}
       		MAX-ACCESS	read-write
       		STATUS		current
       		DESCRIPTION
       			"
       				远端设备命令字，每个设备都有自己固定的命令字
       				1:复位 ，2：开始查询信息，3：结束查询信息

       				-------------------------------------------
       			   |  bit31-27  |   bit26-22 |      bit21-0    |
       				-------------------------------------------
       			   |端口类型  	|    端口ID  |   命令字        |
					-------------------------------------------
	  				约定：
       				端口类型有5位：
       				        0： 表示设备
       						1	以太网电口
							2	以太网光口
							3	G.SHDSL端口
							4	E1端口(Sa比特不处理)
							5	V35端口
					端口ID有5位：0-31表示32个端口
					命令字有22位：
					        1：硬复位
					        2：软复位
					        3：开始查询统计信息
					        4：结束查询统计信息
					        5：内环使能
					        6：内环禁止
					        7：外环使能
					        8：外环禁止
							9: 无环回
							10: 本地内环使能
							11: 本地外环使能
							12: 本地双向环使能
							13: 远端内环使能
							14: 远端外环使能
							15: 远端双向环使能
							16: 本地内环禁止
							17: 本地外环禁止
							18: 本地双向环禁止
							19: 远端内环禁止
							20: 远端外环禁止
							21: 远端双向环禁止
							22: 端口BERT测试开始
							23: 端口BERT测试结束


				 注意：对于约定四而言，使用rcftRemoteDeviceOrder作为内部变量，按照上面的格式将设备级的命令和
				 端口级的命令转化为一个字符串、综合处理。因此，这就要求rcftRemoteDeviceOrder的枚举值要和各个
				 接口级命令的枚举值完全一致。如果某个接口级的命令添加了一个新的枚举值，就要把其他接口
				 下的命令和rcftRemoteDeviceOrder的枚举值都添加一下。总之，要做到一改全改、始终一致。
       			"
            ::= { rcftRemoteDeviceSysEntry 11 }


       rcftRemoteDeviceConfigFlag OBJECT-TYPE
       		SYNTAX		 INTEGER
       		{
       			set(1)
       		}
       		MAX-ACCESS	 read-write
       		STATUS		 current
       		DESCRIPTION
       			"
       				远端设备的配置标志，绑定对象结束的标志
       			"
       	::= { rcftRemoteDeviceSysEntry 12 }

       rcftRemoteSlotAutoCutErrLineEn OBJECT-TYPE
           SYNTAX INTEGER
           {
                enable(1),
    	        disable(2)
           }
        	MAX-ACCESS read-write
            STATUS current
            DESCRIPTION
            "
            	远端设备误码自动切断功能:(1:使能,2:禁止).
            "
        ::={ rcftRemoteDeviceSysEntry 13 }

        rcftRemotePowerSupply	OBJECT-TYPE
        	SYNTAX	INTEGER
        	{
        		ac220v(1),
        		dc-48v(2),
        		dc24v(3)
        	}
        	MAX-ACCESS read-only
            STATUS current
            DESCRIPTION
            "
            	远端设备的供电方式
            "
        ::={ rcftRemoteDeviceSysEntry 14 }

       rcftRemoteDevicePowerDown	OBJECT-TYPE
       	SYNTAX	INTEGER
       	{
       		normal(1),
       		powerdown(2)
       	}
       	MAX-ACCESS	read-only
       	STATUS	current
       	DESCRIPTION
       	"
       		远端设备掉电状态
       	"
		::={ rcftRemoteDeviceSysEntry 15 }

	  rcftRemoteDeviceClkMode	OBJECT-TYPE
       	SYNTAX	INTEGER
       	{
       		masterClk(1),
       		e1PortClk(2),
       		gPortClk(3),
       		secondary(4),
       		v35PortClk(5),
       		reserved(100)
       	}
       	MAX-ACCESS	read-write
       	STATUS	current
       	DESCRIPTION
       	"
       		远端设备的时钟模式:1：主时钟；2：E1端口时钟；3：G.端口时钟；4:从时钟  100：保留
			两个字节表示：高字节表示时钟源的端口类型，低字节表示端口ID
			端口类型取值分别表示：
			0x00，表示采用内(主)时钟方式
			0x01	以太网电口
			0x02	以太网光口
			0x03	G.SHDSL端口
			0x04	E1端口(Sa比特不处理)
			0x05	V35端口

       "
		::={ rcftRemoteDeviceSysEntry 16 }

	   rcftRemoteDeviceE1SubCardType	OBJECT-TYPE
		SYNTAX	INTEGER
		MAX-ACCESS read-only
		STATUS current
		DESCRIPTION
		"
			远端设备上E1子卡类型

	  		数值和设备的对应关系是：
	  		0： RC2002-SUB_1E1
			1： RC2002-SUB_2E1
			2： RC954－SUB－4E1－BL
			3： RC954－SUB－8E1－BL
			4： RC2802-SUB-4E1
			5： RC832-SUB-8E1
			6： RC832-SUB-8E1-BL
			7： RC832-SUB-4E1-BL
			8： RC954－SUB－8E1
		"
		::={ rcftRemoteDeviceSysEntry 17 }

	   rcftRemoteDeviceGateway	OBJECT-TYPE
	   		SYNTAX	OCTET STRING(SIZE (0..30))
	   		MAX-ACCESS	read-write
	   		STATUS	current
	   		DESCRIPTION
	   		"
	   			表示设备的网关
	   		"
	  	   ::={rcftRemoteDeviceSysEntry 18}

	   rcftRemoteDeviceIP	OBJECT-TYPE
	   		SYNTAX	OCTET STRING(SIZE (0..30))
	   		MAX-ACCESS	read-write
	   		STATUS	current
	   		DESCRIPTION
	   		"
	   			表示设备的IP地址
	   		"
	  	   ::={rcftRemoteDeviceSysEntry 19}

	   rcftRemoteDeviceSubnetMask	OBJECT-TYPE
	   		SYNTAX	OCTET STRING(SIZE (0..30))
	   		MAX-ACCESS	read-write
	   		STATUS	current
	   		DESCRIPTION
	   		"
	   			表示设备的子网掩码
	   		"
	  	   ::={rcftRemoteDeviceSysEntry 20}

	  	rcftRemoteDeviceVLANID	OBJECT-TYPE
	  		SYNTAX	INTEGER
	  		MAX-ACCESS 	read-write
	  		STATUS	current
	  		DESCRIPTION
	  		"
	  			远端设备的VLAN ID
	  		"
	  	   ::={rcftRemoteDeviceSysEntry 21}

	  	rcftRemoteDeviceCommunityRW	OBJECT-TYPE
	  		SYNTAX	INTEGER
	    	{
	    		read(1),
	    		readwrite(2),
	    		clear(3)
	    	}
	  		MAX-ACCESS 	read-write
	  		STATUS	current
	  		DESCRIPTION
	  		"
	  			远端设备的共同体属性
	  			1:只读
	  			2:读写
	  			3:清除共同体属性
	  		"
	  	   ::={rcftRemoteDeviceSysEntry 22}

	  	rcftRemoteDeviceCommunityLength	OBJECT-TYPE
	  		SYNTAX	INTEGER
	  		MAX-ACCESS 	read-write
	  		STATUS	current
	  		DESCRIPTION
	  		"
	  			远端设备的共同体名长度
	  		"
	  	   ::={rcftRemoteDeviceSysEntry 23}

	    rcftRemoteDeviceCommunity	OBJECT-TYPE
	    	SYNTAX	OCTET STRING(SIZE (0..30))
	    	MAX-ACCESS	read-write
	    	STATUS	current
	    	DESCRIPTION
	    	"
	    		远端设备的共同体名
	    	"
	  	   ::={rcftRemoteDeviceSysEntry 24}

	    rcftRemoteDeviceVoltageValue	OBJECT-TYPE
	       	SYNTAX  Unsigned32
	       	MAX-ACCESS	read-only
	       	STATUS	current
	       	DESCRIPTION
	       	"
	       		每八位表示一个电压值,
	       		第一个8位表示3.3V的电压值,第二个8位表示2.5V的电压值,
	       		第三个8位表示1.8V的电压值,第四个高8位表示1.2V的电压值
	       		--------------------------------------------
	       	    |    4    |     3    |     2     |     1    |
	       		--------------------------------------------

	       	"
	       ::={rcftRemoteDeviceSysEntry 25}

	     rcftRemoteDeviceStatus	OBJECT-TYPE
	      	SYNTAX	INTEGER
	      	MAX-ACCESS	read-write
	      	STATUS	current
	      	DESCRIPTION
	      	"
	      	   BIT19		对端设备工作模式 0：有损 1：无损
	      	   BIT18		本端设备工作模式 0：有损 1：无损
	      	   BIT17	  	0：单电口，1：多电口
	      	   BIT16	  	双向保护倒换。0：禁止，1：使能
	      	   BIT15	  	返回模式。0：非返回, 1：返回
	      	   BIT14	  	E-6倒换条件启用。0：不启用，1：启用
	      	   BIT13	  	当前的工作通道。0：pri，1：sec
	      	   BIT11-BIT12	工作通道选择方式。00：自动保护倒换, 01：手动倒换 								10：强制倒换, 11：保留
	      	   BIT10	  	工作通道选择。0：pri，1：sec
	      	   BIT9	  故障转移。1：使能，2：禁止
	      	   BIT8	  屏蔽告警音 1：屏蔽  0：不屏蔽
	      	   BIT7	  光口的ALS功能  0：不使能    1：使能
	      	   BIT6   Power2工作状态 1：工作正常  0：工作异常或未接
	      	   BIT5   Power1工作状态 1：工作正常  0：工作异常或未接
	      	   BIT4   对端总告警 1：正常  0：告警
	      	   BIT3   本地总告警 1：正常  0：告警
	      	   BIT2   E1未用支路告警屏蔽状态 1：屏蔽  0：不屏蔽
	      	   BIT1-0 光口倒换功能状态 00：自动保护倒换   01：强制选择B 10：强制选择A
	      	"
	      	::={rcftRemoteDeviceSysEntry 26}

	      rcftRemoteSubModuleExist	OBJECT-TYPE
	      	SYNTAX	INTEGER
	      	MAX-ACCESS	read-only
	      	STATUS	current
	      	DESCRIPTION
	      	"
				每一位表示扩展槽N子卡的在位状态：0：不在位，1：在位
	      	"
	     	::={rcftRemoteDeviceSysEntry 27}

	  rcftRemoteMultiE1LoopOrder	OBJECT-TYPE
	  		SYNTAX	OCTET STRING(SIZE (0..64))
			MAX-ACCESS	read-write
			STATUS	current
			DESCRIPTION
			"
			   针对四路E1环回的命令节点
               每一字节表示一路E1的环回命令
               0：本地环回，1：无本地环回：，2：远端环回，3：无远端环回
			"
            ::={rcftRemoteDeviceSysEntry 28}


		rcftRemoteOrderTimeParameter OBJECT-TYPE
			SYNTAX	INTEGER
			MAX-ACCESS read-write
			STATUS	current
			DESCRIPTION
	  		 "
	  		    给远端模块发送命令时所需要赋的时长参数。

	  		    1: 测试时长1分钟
	  		    2: 测试时长2分钟
	  		    3: 测试时长4分钟
	  		    4: 测试时长8分钟
	  		    5: 测试时长15分钟
	  		    6: 测试时长30分钟
	  		    7: 测试时长60分钟

	  		    18: 测试2帧
	  		    19: 测试5帧
	  		    20: 测试10帧
	  		    21: 测试20帧
	  		    22: 测试50帧
	  		    23: 测试100帧
	  		"
            ::= { rcftRemoteDeviceSysEntry 29 }


      	rcftRemoteOrderModeParameter OBJECT-TYPE
			SYNTAX	INTEGER
			MAX-ACCESS read-write
			STATUS	current
			DESCRIPTION
	  		 "
	  		    给远端模块发送命令时所需要赋的模式参数。

	  		"
            ::= { rcftRemoteDeviceSysEntry 30 }

        rcftRemoteSDRAMBuf OBJECT-TYPE
			SYNTAX	INTEGER
			MAX-ACCESS read-write
			STATUS	current
			DESCRIPTION
	  		 "
	  		    设置远端SDRAM大小
	  		    之前定义的是
	  		    1:小缓存
	  		    2:大缓存

	  		    以后用以下枚举值：
	  		    1：半用		2：全用		3：四分之一占用		4：八分之一占用

	  		"
            ::= { rcftRemoteDeviceSysEntry 31 }

         rcftRemoteRLPStatus OBJECT-TYPE
			SYNTAX	INTEGER
			MAX-ACCESS read-only
			STATUS	current
			DESCRIPTION
	  		 "
	  		    远端RLP灯状态
	  		    1：RLP灯灭
				2：RLP绿闪
				3：RLP绿常亮
				4：RLP黄闪
				5：RLP黄常亮
	  		"
            ::= { rcftRemoteDeviceSysEntry 32 }

         rcftRemoteLALStatus	OBJECT-TYPE
	    	SYNTAX INTEGER
	    	MAX-ACCESS read-only
	    	STATUS current
	    	DESCRIPTION
	    	"
	    	 	0: 灭
	    	 	1:黄闪亮
	    	 	2:黄常亮
	    	 	3:红闪亮
	    	 	4:红常亮

	    	"
	    	::= { rcftRemoteDeviceSysEntry 33 }

	     rcftRemoteRALStatus	OBJECT-TYPE
	    	SYNTAX INTEGER
	    	MAX-ACCESS read-only
	    	STATUS current
	    	DESCRIPTION
	    	"
	    	 	0: 灭
	    	 	1:黄闪亮
	    	 	2:黄常亮
	    	 	3:红闪亮
	    	 	4:红常亮

	    	"
	        ::= { rcftRemoteDeviceSysEntry 34 }

	     rcftRemoteDeviceSwitchStatus	OBJECT-TYPE
	      	SYNTAX	INTEGER
	      	MAX-ACCESS	read-only
	      	STATUS	current
	      	DESCRIPTION
	      	"
	      	   BIT0	  光口的ALS开关功能  0：禁止    1：使能
	      	"
	      	::={rcftRemoteDeviceSysEntry 35}

	     rcftRemoteDeviceMoudleExist	OBJECT-TYPE
	      	SYNTAX	INTEGER
	      	MAX-ACCESS	read-only
	      	STATUS	current
	      	DESCRIPTION
	      	"
	      	   BIT3	  第四个扩展子卡的在位  0：不在位    1：在位
	      	   BIT2	  第三个扩展子卡的在位  0：不在位    1：在位
	      	   BIT1	  第二个扩展子卡的在位  0：不在位    1：在位
	      	   BIT0	  第一个扩展子卡的在位  0：不在位    1：在位
	      	"
	      	::={rcftRemoteDeviceSysEntry 36}


        rcftRemoteCardInformation OBJECT-TYPE
	  		SYNTAX	OCTET STRING(SIZE (0..30))
			MAX-ACCESS	read-only
			STATUS	current
			DESCRIPTION
			"
			  订货信息，
    		对于光端机来说： 例如：RCMS1000-504A-XX 。
    			其中：XXXX表示4个扩展槽的小模块是否存在及类型。每个X表示一个槽位是否存在小模块：
				０：无，Ｄ：有数据，Ａ：有音频，Ｖ：有视频，E：有以太口，1：有非智能
			"
            ::={rcftRemoteDeviceSysEntry 37}

            rcftRemoteSwitchType		OBJECT-TYPE
	      	SYNTAX	INTEGER
	      	MAX-ACCESS	read-write
	      	STATUS	current
	      	DESCRIPTION
	      	"
	      		交换模式：
	      		1：全交换
	      		2：端口隔离
	      		3：VLAN模式
	      	"
	      	::={rcftRemoteDeviceSysEntry 38}


            rcftRemoteConnectMode	OBJECT-TYPE
	      	SYNTAX	INTEGER
	      	MAX-ACCESS	read-only
	      	STATUS	current
	      	DESCRIPTION
	      	"
	      	    对通模式：
	      	    1：不对通；
				2：模式1（与RJ017对通）；
				3：模式2（与RC7221对通）。
	      	"
	      	::={rcftRemoteDeviceSysEntry 39}

            rcftRemoteQosEnable		OBJECT-TYPE
	      	SYNTAX	INTEGER
	      	MAX-ACCESS	read-write
	      	STATUS	current
	      	DESCRIPTION
	      	"
	      	    Qos使能/禁止：
	      	    1：使能
	      	    2：禁止
	      	"
	      	::={rcftRemoteDeviceSysEntry 40}

            rcftRemoteBaseCOS		OBJECT-TYPE
	      	SYNTAX	INTEGER
	      	MAX-ACCESS	read-write
	      	STATUS	current
	      	DESCRIPTION
	      	"
	      	   Base COS，范围0~7。
			   从以太口进入的带tag数据包如果它的tag中COS值大于等于此值，则此数据包为高优先级，
			   反之为低优先级。
	      	"
	      	::={rcftRemoteDeviceSysEntry 41}

            rcftRemoteDSCP		OBJECT-TYPE
	  		SYNTAX	OCTET STRING(SIZE (0..65))
			MAX-ACCESS	read-write
			STATUS	current
			DESCRIPTION
			"
			  DSCP映射。（OCTET STRING）。
			   字节顺序为从右到左，分别表示0~63字节，表示DSCP[0~63]。
			   每一字节为1表示IP帧头相应的DSCP（TOS）域的数据包为高优先级，为0则为低优先级。

			   例如：rcftRemoteDSCP  字节60=1、字节50=1，其他bit为0。
			   		表示DSCP域为111100、110010的数据包为高优先级，其他的为低优先级。
			"
            ::={rcftRemoteDeviceSysEntry 42}

            rcftRemoteQueuesPolicy 	OBJECT-TYPE
	      	SYNTAX	INTEGER
	      	MAX-ACCESS	read-write
	      	STATUS	current
	      	DESCRIPTION
	      	"
	      	  	队列调度策略
					1:严格优先
					2：加权循环（高：低）10:1；
					3：加权循环（高：低）5:1；
					4：加权循环（高：低）2:1；
	      	"
	      	::={rcftRemoteDeviceSysEntry 43}

         rcftRemoteMultiE1AlarmRejectOrder	OBJECT-TYPE
	  		SYNTAX	OCTET STRING(SIZE (0..64))
			MAX-ACCESS	read-write
			STATUS	current
			DESCRIPTION
			"
			   针对E1告警屏蔽的命令节点
               每一字节表示一路E1的告警屏蔽命令
               1：屏蔽
               2：不屏蔽

               该字符串中从左到右分别表示对第1－N路E1的告警屏蔽操作
			"
            ::={rcftRemoteDeviceSysEntry 44}

        rcftRemoteT1PortPulseWaveForm  OBJECT-TYPE
       		SYNTAX	INTEGER
       		MAX-ACCESS read-write
       		STATUS	current
       		DESCRIPTION
       		"
       	    	T1脉冲波形

       	    		2：T1传输距离为0~133ft
					3：T1传输距离为133~266ft
					4：T1传输距离为266~399ft
					5：T1传输距离为399~533ft
					6：T1传输距离为533~655ft

       		"
       		::= { rcftRemoteDeviceSysEntry 45 }

       	rcftRemoteT1PortCodeType	  OBJECT-TYPE
       		SYNTAX	INTEGER
       		MAX-ACCESS read-write
       		STATUS	current
       		DESCRIPTION
       		"
       	    	T1的编码类型
       	    		1：B8ZS
       	    		2：AMI
       		"
        	::= { rcftRemoteDeviceSysEntry 46 }

        rcftRemoteDeviceSabitMode  OBJECT-TYPE
       		SYNTAX	INTEGER
       		MAX-ACCESS read-only
       		STATUS	current
       		DESCRIPTION
       		"
       	    	Sabit 的工作模式
       	    	bit1-0：Sa4；
       	    	bit3-2：Sa5；
       	    	bit5-4：Sa6；
       	    	bit7-6：Sa7
       	    	bit9-8：Sa8

       	    	00：字节模式，（00：代表默认的模式，字节模式）
				01：HDLC模式
				10：禁止
       		"
        	::= { rcftRemoteDeviceSysEntry 47 }

       	rcftRemoteDeviceApsWaitToRestore OBJECT-TYPE
       		SYNTAX INTEGER (0..255)
       		MAX-ACCESS read-write
       		STATUS current
       		DESCRIPTION
       		"
      	    	-- 设备保护倒换自恢复时间，设备恢复到主通道的时间,以分钟为单位
      	    	-- 缺省值为12，可以设置范围为0－255
       		"
       		::= { rcftRemoteDeviceSysEntry 48 }

       	rcftRemoteDeviceCLKChannel	OBJECT-TYPE
       		SYNTAX	INTEGER
       		MAX-ACCESS read-only
       		STATUS	current
       		DESCRIPTION
       		"
				从时钟选取的E1编号，范围：1-设备E1端口数
       		"
        	::= { rcftRemoteDeviceSysEntry 49 }

        rcftRemoteDeviceRmcChannelType	OBJECT-TYPE
       		SYNTAX	INTEGER
       		MAX-ACCESS read-write
       		STATUS	current
       		DESCRIPTION
       		"
       	    	收发器网管通道模式：1：802.3ah，2：rclink， 3：TS1000，	10：远端收发器网管禁止
       		"
        	::= { rcftRemoteDeviceSysEntry 50 }

        rcftRemoteDeviceProductType OBJECT-TYPE
            SYNTAX OCTET STRING(SIZE (0..10))
          	MAX-ACCESS read-only
          	STATUS current
          	DESCRIPTION
          	"
          	    产品型号，ASCII码
          	"
          	::={rcftRemoteDeviceSysEntry 51}

	   	rcftRemoteDeviceProtocolVer   OBJECT-TYPE
	   		SYNTAX INTEGER
	   		MAX-ACCESS	read-only
	   		STATUS	current
	   		DESCRIPTION
	   		"
	   			协议版本
			"
	   		::= {rcftRemoteDeviceSysEntry 52}

 	   	rcftRemoteDeviceVenderCode   OBJECT-TYPE
	   		SYNTAX INTEGER
	   		MAX-ACCESS	read-only
	   		STATUS	current
	   		DESCRIPTION
	   		"
	   			vender code，厂家ID。
	   			在移动标准信息中为1字节。
	   			在TS1000标准信息中为3字节，我公司ID为：0x00-0x0E-0x5E。
			"
	   		::= {rcftRemoteDeviceSysEntry 53}

 	   	rcftRemoteDeviceModelID   OBJECT-TYPE
	   		SYNTAX INTEGER
	   		MAX-ACCESS	read-only
	   		STATUS	current
	   		DESCRIPTION
	   		"
	   			Model ID ，表示各厂家私有设备类型。
	   			在TS1000标准信息中为3字节：
						RC521-FE-C的Model ID为 0x00fc24，
						RC521-FE-D的Model ID为 0x00fc00。
			"
	   		::= {rcftRemoteDeviceSysEntry 54}

	   	rcftRemoteE1PortNumber    OBJECT-TYPE
	   		SYNTAX INTEGER
	   		MAX-ACCESS	read-only
	   		STATUS	current
	   		DESCRIPTION
	   		"
	   			设备的E1 端口数
			"
	   		::= {rcftRemoteDeviceSysEntry 55}

	   	rcftRemoteDeviceVLANType 	OBJECT-TYPE
	   		SYNTAX INTEGER
	   		MAX-ACCESS  read-write
	   		STATUS  current
	   		DESCRIPTION
	   		"
	   			设备的VLAN模式
			   		1：no vlan
					2：port vlan
					3：tag vlan
	   		"
	   		::= {rcftRemoteDeviceSysEntry 56}

	  	rcftRemoteDeviceQoSPolicy 	OBJECT-TYPE
	   		SYNTAX INTEGER
	   		MAX-ACCESS  read-write
	   		STATUS  current
	   		DESCRIPTION
	   		"
	   			设备的QoS优先级划分策略：
			   		1：基于端口的
					2：基于COS的
	   		"
	   		::= {rcftRemoteDeviceSysEntry 57}

	   	rcftRemoteDeviceApsE3SwitchDelay OBJECT-TYPE
	   		SYNTAX INTEGER
	   		MAX-ACCESS read-write
	   		STATUS current
	   		DESCRIPTION
	   		"
            	设备保护倒换时，E-3告警切换延时时间，以秒为单位
            	1～15，默认为5
	   		"
	   		::= { rcftRemoteDeviceSysEntry 58}

 	   	rcftRemoteDeviceApsE6SwitchDelay OBJECT-TYPE
	   		SYNTAX INTEGER
	   		MAX-ACCESS read-write
	   		STATUS current
	   		DESCRIPTION
	   		"
            	设备保护倒换时，E-6告警切换延时时间，以秒为单位
            	1～255，默认为60
	   		"
	   		::= { rcftRemoteDeviceSysEntry 59}

	   	rcftRemoteDeviceVLANTagDirection  OBJECT-TYPE
	   		SYNTAX INTEGER
	   		MAX-ACCESS read-write
	   		STATUS current
	   		DESCRIPTION
	   		"
            	VLAN-TAG方向
            		1：光口到电口  2：电口到光口
          	"
	   		::= { rcftRemoteDeviceSysEntry 60}

        rcftRemoteDeviceVLANTagModule  OBJECT-TYPE
	   		SYNTAX INTEGER
	   		MAX-ACCESS read-write
	   		STATUS current
	   		DESCRIPTION
	   		"
            	VLAN-TAG模式
            		1：透传 2：单Tag  3：双Tag  4：保留
          	"
	   		::= { rcftRemoteDeviceSysEntry 61}

        rcftRemoteDeviceISPTPID   OBJECT-TYPE
	   		SYNTAX INTEGER
	   		MAX-ACCESS read-write
	   		STATUS current
	   		DESCRIPTION
	   		"
            	ISP TPID的值，有效值：1~0xfffe, （显示为16进制）
          	"
	   		::= { rcftRemoteDeviceSysEntry 62}


	   rcftRemoteE1DS1PortType OBJECT-TYPE
	      	SYNTAX	INTEGER
	      	MAX-ACCESS read-write
	      	STATUS	current
	      	DESCRIPTION
	      	"
	      	     远端设备E1/T1模式  0：E1, 1：DS1（T1）
	   		"
	   		::= { rcftRemoteDeviceSysEntry 63}

	   rcftRemoteDeviceE1FrameChannel OBJECT-TYPE
	      	SYNTAX	INTEGER
	      	MAX-ACCESS read-write
	      	STATUS	current
	      	DESCRIPTION
	      	"
	      	    成帧的E1支路  0: 均不成帧，1-设备E1数: 成帧的E1支路ID(1 ~设备E1数)
	   		"
	   		::= { rcftRemoteDeviceSysEntry 64}


	   rcftRemoteDeviceManageID OBJECT-TYPE
	      	SYNTAX	INTEGER
	      	MAX-ACCESS read-write
	      	STATUS	current
	      	DESCRIPTION
	      	"
	      	    设备管理ID	1~255
	   		"
	   		::= { rcftRemoteDeviceSysEntry 65}

	   rcftRemoteDeviceMibUse OBJECT-TYPE
	      	SYNTAX	INTEGER
	      	{
	      		mib002(1),
	      		rccomlib(2)
	      	}
	      	MAX-ACCESS read-only
	      	STATUS	current
	      	DESCRIPTION
	      	"
	      	    远端设备支持的mib类型
	      	   	1:使用002mib
			2:使用组件库mib

	      	"
	   		::= { rcftRemoteDeviceSysEntry 66}


 		rcftRemoteDeviceConfigFlagTable OBJECT-TYPE
              SYNTAX  SEQUENCE OF RcftRemoteDeviceConfigFlagEntry
              MAX-ACCESS  not-accessible
              STATUS  current
              DESCRIPTION
                 "
                 "
             ::= { rcftRemoteDeviceSysObjects 2 }

    	rcftRemoteDeviceConfigFlagEntry OBJECT-TYPE
              SYNTAX  RcftRemoteDeviceConfigFlagEntry
              MAX-ACCESS  not-accessible
              STATUS  current
              DESCRIPTION
                 "
                 "
              INDEX   { rcftChassisIndex, rcftSlotIndex,rcftRemoteDeviceIndex }
             ::= { rcftRemoteDeviceConfigFlagTable 1 }

     	RcftRemoteDeviceConfigFlagEntry ::=
              SEQUENCE {
                   rcftRemoteDeviceConfigFinishFlag	INTEGER
				}

	  	rcftRemoteDeviceConfigFinishFlag	OBJECT-TYPE
	  		SYNTAX	INTEGER
	  		MAX-ACCESS 	read-write
	  		STATUS	current
	  		DESCRIPTION
	  		"
	  			第一层远端设备配置结束标志。新设备中用该标志来表明远端配置当次SNMP操作结束。
	  			具体哪些设备用该标志，将在配置说明文档中详细说明。
	  		"
	  	   ::={rcftRemoteDeviceConfigFlagEntry 1}

----------------------------------------------------------------------------
------------------RMOTE DEVICE FE TABLE
----------------------------------------------------------------------------

      --   Fe Current table
	     rcftRemoteEthFePortTable OBJECT-TYPE
              SYNTAX  SEQUENCE OF RcftRemoteEthFePortEntry
              MAX-ACCESS  not-accessible
              STATUS  current
              DESCRIPTION
              "
                 The Remote Device Fe Port table.
              "
             ::= { rcftRemoteDeviceEthFeObjects 1 }

   			rcftRemoteEthFePortEntry OBJECT-TYPE
              SYNTAX  RcftRemoteEthFePortEntry
              MAX-ACCESS  not-accessible
              STATUS  current
              DESCRIPTION
              "
                 An entry in the Fe Port config table.
              "
              INDEX   { rcftChassisIndex, rcftSlotIndex,rcftRemoteDeviceIndex,  rcftRemoteEthFeIndex }
             ::= { rcftRemoteEthFePortTable 1 }

          RcftRemoteEthFePortEntry ::=
              SEQUENCE {
              			rcftRemoteEthFeIndex                     Integer32,
                    	rcftRemoteEthFeLinkStatus                INTEGER,
          			    rcftRemoteEthFeShutDown                  INTEGER,
          			    rcftRemoteEthFeAutoNegotiation           INTEGER,
          			    rcftRemoteEthFeSpeed                	 INTEGER,
						rcftRemoteEthFeDuplex                    INTEGER,
						rcftRemoteEthFeFlowControl				 INTEGER,
						rcftRemoteEthFeRestrictSpeed			 INTEGER,
						rcftRemoteEthFeFaultPass				 INTEGER,
						rcftRemoteEthFeDisabledByRemoteTP		 INTEGER,
						rcftRemoteEthFeDisabledByFxToFeFP		 INTEGER,
						rcftRemoteEthFeTxRestrictSpeed			 INTEGER,
						rcftRemoteEthFeTag						 INTEGER,
						rcftRemoteEthFePortStatus				 INTEGER,
						rcftRemoteEthFeRestrictSpeedStep		 INTEGER,
						rcftRemoteEthFeOrderTimeParameter		 INTEGER,
						rcftRemoteEthFeOrderModeParameter		 INTEGER,
						rcftRemoteEthFeOrder					 INTEGER,
						rcftRemoteEthFePortStatusExtend 	INTEGER,
						rcftRemoteEthFeStormControl			INTEGER,
						rcftRemoteEthFePVID					INTEGER,
						rcftRemoteEthFeDefaultCOS			INTEGER,
						rcftRemoteEthFeQoSPolicy			INTEGER
						}

            rcftRemoteEthFeIndex OBJECT-TYPE
					SYNTAX Integer32
					MAX-ACCESS read-only
					STATUS current
					DESCRIPTION
					"
						远端设备以太网电口端口索引
					"
					::= { rcftRemoteEthFePortEntry 1 }

	   		rcftRemoteEthFeLinkStatus OBJECT-TYPE
					SYNTAX INTEGER
					{
						linkup(1),
						linkdown(2)
					}
					MAX-ACCESS read-only
					STATUS current
					DESCRIPTION
					"
						远端设备以太网电口的link状态
					"
					::= { rcftRemoteEthFePortEntry 2 }

	 		rcftRemoteEthFeShutDown OBJECT-TYPE
					SYNTAX INTEGER
					{
						open(1),
						close(2),
						closebyLocalOtherPortFault(3),
						closebyOppositeFePortFault(4),
						closebyLoopBack(5)

					}
					MAX-ACCESS read-write
					STATUS current
					DESCRIPTION
					"
						远端设备以太网电口的开关使能
						1：电口开；2：电口关；
						3：电口因为本地其它口故障关；
						4：电口因为对端设备电口故障关
					"
					::= { rcftRemoteEthFePortEntry 3 }

		   rcftRemoteEthFeAutoNegotiation OBJECT-TYPE
			        SYNTAX INTEGER
			        {
			            auto(1),
			            manul(2)
			        }
			        MAX-ACCESS read-write
			        STATUS current
			        DESCRIPTION
			          "
			          远端设备电口速率协商方式（1:自协商,2:手动）.
			          This object indicating the negoation mode of the electronic port
			          in the local module.When the value is 1 the eletronic port is
			          set to auto negotiation,otherwise the eletronic port is set to manual negotiation.
			          "
          			::= { rcftRemoteEthFePortEntry 4 }

		  rcftRemoteEthFeSpeed OBJECT-TYPE
		       SYNTAX INTEGER
		        {
		            rcft10Mbps(1),
		            rcft100Mbps(2),
		            rcft1000Mbps(3),
		            rcft10Gbps(4),
		            other(16)
		        }
		        MAX-ACCESS read-write
		        STATUS current
		        DESCRIPTION
		          "
		            远端设备电口的速率.
		            The speed of the electronic port.
		            1、10Mbps
		            2、100Mbps
		            3、1000Mbps
		            4、10Gbps
		            5、other
		          "
		          ::= { rcftRemoteEthFePortEntry 5 }


		 rcftRemoteEthFeDuplex OBJECT-TYPE
		        SYNTAX INTEGER
		        {
		            full-duplex(1),
		            half-duplex(2)
		        }
		        MAX-ACCESS read-write
		        STATUS current
		        DESCRIPTION
		          "
		          远端设备电口双工模式（1:全双工，2:半双工）.
		          The duplex mode of the electronic port.
		          1:full duplex
		          2:half duplex
		          "
		         ::= { rcftRemoteEthFePortEntry 6 }


         rcftRemoteEthFeFlowControl OBJECT-TYPE
         		SYNTAX	INTEGER
         		{
         		     enable(1),
         		     disable(2)
         		}
	          MAX-ACCESS  read-write
	          STATUS  current
	          DESCRIPTION
	                 "
	                 	远端设备以太网端口流控功能使能(1:使能，2:禁止)
	                 "
			 ::= { rcftRemoteEthFePortEntry 7 }

		rcftRemoteEthFeRestrictSpeed	OBJECT-TYPE
				SYNTAX	INTEGER
				MAX-ACCESS	read-write
				STATUS	current
				DESCRIPTION
					"
						远端设备以太网端口接收限定速率：(n * value；n = 0,1,2....2^12. value = 32kb/s).
					"
			 ::= { rcftRemoteEthFePortEntry 8 }

		rcftRemoteEthFeFaultPass	OBJECT-TYPE
				SYNTAX INTEGER
				{
					enable(1),
					disable(2)
				}
				MAX-ACCESS	read-write
				STATUS	current
				DESCRIPTION
					"
						远端设备以太网端口故障转移功能(1:使能，2:禁止)
					"
				 ::= { rcftRemoteEthFePortEntry 9 }

		rcftRemoteEthFeDisabledByRemoteTP	OBJECT-TYPE
			SYNTAX INTEGER
			{
				open(1),
				close(2)
			}
			MAX-ACCESS	read-only
			STATUS	current
			DESCRIPTION
			"
				远端设备以太网电口关闭的原因是由于对端电口linkdown
			"
			::= { rcftRemoteEthFePortEntry 10 }

		rcftRemoteEthFeDisabledByFxToFeFP	OBJECT-TYPE
			SYNTAX INTEGER
			{
				open(1),
				close(2)
			}
			MAX-ACCESS	read-only
			STATUS	current
			DESCRIPTION
			"
				远端设备以太网电口关闭的原因是由于光到电故障转移功能使能
			"
			::= { rcftRemoteEthFePortEntry 11 }

		rcftRemoteEthFeTxRestrictSpeed		OBJECT-TYPE
			SYNTAX	INTEGER
			MAX-ACCESS	read-write
			STATUS	current
			DESCRIPTION
			"
				远端设备以太网电口发送限定速率。其最大值视板卡而不同。
			"
			::= { rcftRemoteEthFePortEntry 12 }


		rcftRemoteEthFeTag	OBJECT-TYPE
			SYNTAX INTEGER
			{
				tag(1),
				untag(2)
			}
			MAX-ACCESS read-write
			STATUS	current
			DESCRIPTION
			"
				远端设备以太网电口的标签
			"
		    ::= { rcftRemoteEthFePortEntry 13 }

		 rcftRemoteEthFePortStatus	OBJECT-TYPE
		 	SYNTAX INTEGER
		 	MAX-ACCESS read-write
		 	STATUS	current
		 	DESCRIPTION
		 	"
                BIT5    LOC_FP_EN   1：使能本地其它端口故障向电口转移；0：禁止。
                BIT4    REM_FP_EN	1：使能远端电口故障向电口转移；    0：禁止。
                BIT3-2  MDIX_Valid 	00：电口允许自交叉且工作于SW方式；
                                    01：电口允许自交叉且工作于NIC方式；
                                    10：电口禁止自交叉，设置工作于SW方式；
                                    11：电口禁止自交叉。设置工作于NIC方式。
				BIT1-0  保留
		 	"
	        ::= { rcftRemoteEthFePortEntry 14 }

	 	rcftRemoteEthFeRestrictSpeedStep	OBJECT-TYPE
	 		SYNTAX	INTEGER
	 		MAX-ACCESS	read-only
	 		STATUS		current
	 		DESCRIPTION
	 		"
	 			带宽粒度
	 			0x00：64Kbps；
	 			0x01：32Kbps（无）；
	 			0x02：80Kbps;
				0x03：800Kbps;
				0x04：8000Kbps;
				其余：保留。
	 		"
			::= { rcftRemoteEthFePortEntry 15 }

		rcftRemoteEthFeOrderTimeParameter OBJECT-TYPE
			SYNTAX	INTEGER
			MAX-ACCESS read-write
			STATUS	current
			DESCRIPTION
	  		 "
	  		    给远端模块发送命令时所需要赋的时长参数。

	  		    1: 测试时长1分钟
	  		    2: 测试时长2分钟
	  		    3: 测试时长4分钟
	  		    4: 测试时长8分钟
	  		    5: 测试时长15分钟
	  		    6: 测试时长30分钟
	  		    7: 测试时长60分钟

	  		    18: 测试2帧
	  		    19: 测试5帧
	  		    20: 测试10帧
	  		    21: 测试20帧
	  		    22: 测试50帧
	  		    23: 测试100帧
	  		"
            ::= { rcftRemoteEthFePortEntry 16 }

      	rcftRemoteEthFeOrderModeParameter OBJECT-TYPE
			SYNTAX	INTEGER
			MAX-ACCESS read-write
			STATUS	current
			DESCRIPTION
	  		 "
	  		    给远端模块发送命令时所需要赋的模式参数。

	  		"
            ::= { rcftRemoteEthFePortEntry 17 }

		rcftRemoteEthFeOrder	OBJECT-TYPE
			SYNTAX	INTEGER
			MAX-ACCESS	read-write
			STATUS	current
			DESCRIPTION
			"
			    1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
				22: 端口BERT测试开始
				23: 端口BERT测试结束


			注意：rcftRemoteE1Order的枚举值要和rcftRemoteDeviceOrder始终保持完全一致。
			"
		   ::= { rcftRemoteEthFePortEntry 18 }


		   rcftRemoteEthFePortStatusExtend	OBJECT-TYPE
	      	SYNTAX	INTEGER
	      	MAX-ACCESS	read-write
	      	STATUS	current
	      	DESCRIPTION
	      	"
	      		由于501b/502b/504a视频光端机以太口信息没有遵循002标准子块，因此在这里单独
	      		定义一个节点表示视频光端机以太口信息

	      	   bit15-8:  视频光端机以太口的位置信息
	      	   bit15-12：盘 （0代表基盘。002目前只有基盘，固定bit7-4为全0）
			   bit11-8： 槽 （1~15:扩展槽）

	      	   BIT4 link	1：linkup		0：linkdown
	      	   BIT3	开关	1：打开			0：关闭
	      	   BIT2	自适应  1：使能			0：禁止
	      	   BIT1	双工  	1：全双工，		0：半双工
	      	   BIT0	速率，	1：100M，		0：10M
	      	"
	      	::={rcftRemoteEthFePortEntry 19}

	      	rcftRemoteEthFeStormControl			OBJECT-TYPE
	      	SYNTAX	INTEGER
	      	MAX-ACCESS	read-write
	      	STATUS	current
	      	DESCRIPTION
	      	"
                广播风暴抑制。
					1：使能，2：禁止。

	      	"
	      	::={rcftRemoteEthFePortEntry 20}

			rcftRemoteEthFePVID					OBJECT-TYPE
	      	SYNTAX	INTEGER
	      	MAX-ACCESS	read-write
	      	STATUS	current
	      	DESCRIPTION
	      	"
	      		PVID。范围：1~4094
	      	"
	      	::={rcftRemoteEthFePortEntry 21}

			rcftRemoteEthFeDefaultCOS			OBJECT-TYPE
	      	SYNTAX	INTEGER
	      	MAX-ACCESS	read-write
	      	STATUS	current
	      	DESCRIPTION
	      	"
	      		默认COS值。范围：0~7
	      	"
	      	::={rcftRemoteEthFePortEntry 22}

			rcftRemoteEthFeQoSPolicy			OBJECT-TYPE
	      	SYNTAX	INTEGER
	      	MAX-ACCESS	read-write
	      	STATUS	current
	      	DESCRIPTION
	      	"
	      		 QoS优先级划分策略。
					Bit2：DSCP使能。1：使能，0：禁止
					Bit1：COS使能。1：使能，0：禁止
					Bit0：端口优先级。1：高优先级，0：低优先级。
	      	"
	      	::={rcftRemoteEthFePortEntry 23}




-- --------------------------------------------------------------------------
-- ----------------REMOTE DEVICE FX TABLE
-- --------------------------------------------------------------------------

        rcftRemoteEthFxPortTable OBJECT-TYPE
              SYNTAX  SEQUENCE OF RcftRemoteEthFxPortEntry
              MAX-ACCESS  not-accessible
              STATUS  current
              DESCRIPTION
                 "
                 The Remote Device FX Port table.
                 "
             ::= { rcftRemoteDeviceEthFxObjects 1 }

   		rcftRemoteEthFxPortEntry OBJECT-TYPE
              SYNTAX  RcftRemoteEthFxPortEntry
              MAX-ACCESS  not-accessible
              STATUS  current
              DESCRIPTION
                 "
                 An entry in the Fx Port config table.

                 "
              INDEX   { rcftChassisIndex, rcftSlotIndex,rcftRemoteDeviceIndex, rcftRemoteEthFxIndex }
             ::= { rcftRemoteEthFxPortTable 1 }

          RcftRemoteEthFxPortEntry ::=
              SEQUENCE {
                    rcftRemoteEthFxIndex                        Integer32,
                    rcftRemoteEthFxFlowControl					INTEGER,
                    rcftRemoteEthFxPortRLK                     	INTEGER,
          			rcftRemoteEthFxPortTLK                     	INTEGER,
          			rcftRemoteEthFxPortSD           			INTEGER,
          			rcftRemoteEthFxPortTxPowerAbnormal			INTEGER,
					rcftRemoteEthFxPortRxSensitiveAbnormal     	INTEGER,
					rcftRemoteEthFxPortLaserAbnormal           	INTEGER,
					rcftRemoteEthFxShutDown                  	INTEGER,
					rcftRemoteEthFxModuleType					INTEGER,
					rcftRemoteEthFxFaultPass					INTEGER,
					rcftRemoteEthFxPortLink 					INTEGER,
					rcftRemoteEthFxRxToTxFaultPass				INTEGER,
					rcftRemoteEthFxTxDisabledByFR				INTEGER,
					rcftRemoteEthFxOrderTimeParameter		 	INTEGER,
					rcftRemoteEthFxOrderModeParameter		 	INTEGER,
					rcftRemoteEthFxOrder					 	INTEGER,
					rcftRemoteEthFxPortExist 		INTEGER,
					rcftRemoteEthFxPortAuto			INTEGER,
					rcftRemoteEthFxModuleMaxSpeed   INTEGER,
					rcftRemoteEthFxTranDistance		INTEGER,
					rcftRemoteEthFxModuleWaveLen	INTEGER,
					rcftRemoteEthFxPortConnectorType	INTEGER,
					rcftRemoteEthFxPortTransmitMedia	INTEGER,
					rcftRemoteEthFxModuleManufacturer	OCTET STRING,
					rcftRemoteEthFxModuleDescr			OCTET STRING,
					rcftRemoteEthFxPortModuleVersion			OCTET STRING,
					rcftRemoteEthFxModuleSerialNumber	OCTET STRING,
					rcftRemoteEthFxPortSFPDiagnoInfo	INTEGER,
					rcftRemoteEthFxSFPDiagnoAlarmStatus	INTEGER,
					rcftRemoteEthFxPortStatus		INTEGER,
					rcftRemoteEthFxUntag	INTEGER,
					rcftRemoteEthFxPVID		INTEGER,
					rcftRemoteEthFxPortSFPType INTEGER,
					rcftRemoteEthFxPortSFPInfo	INTEGER,
					rcftRemoteEthFxPortLoopStatus	INTEGER,
					rcftRemoteEthFxPortRxRestrictSpeed	INTEGER,
					rcftRemoteEthFxPortTxRestrictSpeed	INTEGER,
					rcftRemoteEthFxSFPDiagnoWarningStatus	INTEGER,
					rcftRemoteEthFxPortLineOrClient	INTEGER,
                    rcftRemoteEthFxCOS		INTEGER

                   }

          rcftRemoteEthFxIndex OBJECT-TYPE
          		SYNTAX  	Integer32
          		MAX-ACCESS  read-only
          		STATUS  	current
          		DESCRIPTION
                 "
                 远端设备光口的索引
                 "
   		  		::= { rcftRemoteEthFxPortEntry 1 }

		 rcftRemoteEthFxFlowControl  OBJECT-TYPE
		 	   SYNTAX INTEGER{
		 	             enable(1),
		 	             disable(2)
		 	   }
	          MAX-ACCESS  read-write
	          STATUS  current
	          DESCRIPTION
	                 "
	                 	远端设备以太网端口流控功能使能(1:使能，2:禁止)
	                 "
			  ::= { rcftRemoteEthFxPortEntry 2 }



         rcftRemoteEthFxPortRLK OBJECT-TYPE
	          SYNTAX  INTEGER
	          {
	             link(1),
	             unlink(2)
	          }
	          MAX-ACCESS  read-only
	          STATUS  current
	          DESCRIPTION
	           "
	              远端设备光口RLK
	           "

		  	  ::= { rcftRemoteEthFxPortEntry 3 }

   		  rcftRemoteEthFxPortTLK OBJECT-TYPE
	          SYNTAX  INTEGER
	          		 {
	                     link(1),
	                     unlink(2)
	                 }
	          MAX-ACCESS  read-only
	          STATUS  current
	          DESCRIPTION
	          "
	                远端设备光口TLK
	          "

	          ::= { rcftRemoteEthFxPortEntry 4 }


        rcftRemoteEthFxPortSD OBJECT-TYPE
	          SYNTAX  INTEGER
	           {
	              normal (1),
	              sd (2)
	           }
	          MAX-ACCESS  read-only
	          STATUS  current
	          DESCRIPTION
	          "
	             远端设备光口SD异常
	          "

			  ::= { rcftRemoteEthFxPortEntry 5 }


		rcftRemoteEthFxPortTxPowerAbnormal OBJECT-TYPE
		     SYNTAX  INTEGER
		     {
		        normal (1),
		        abnormal (2)
		     }
		     MAX-ACCESS  read-only
		     STATUS  current
		     DESCRIPTION
		     "
		        远端设备发送功率异常
		     "

		  ::= { rcftRemoteEthFxPortEntry 6 }

		 rcftRemoteEthFxPortRxSensitiveAbnormal OBJECT-TYPE
          	SYNTAX  INTEGER
          	{
               normal (1),
               abnormal (2)
            }
          	MAX-ACCESS  read-only
          	STATUS  current
          	DESCRIPTION
            "
                 远端设备接收灵敏度异常
            "

		  	::= { rcftRemoteEthFxPortEntry 7 }

		  rcftRemoteEthFxPortLaserAbnormal OBJECT-TYPE
	          SYNTAX  INTEGER
	          {
	             normal (1),
	             abnormal (2)
	          }
	          MAX-ACCESS  read-only
	          STATUS  current
	          DESCRIPTION
	          "
	              远端设备光激光管工作异常
	          "
			  ::= { rcftRemoteEthFxPortEntry 8 }

	 	 rcftRemoteEthFxShutDown OBJECT-TYPE
					SYNTAX INTEGER
					{
						open(1),
						close(2),
						closeByFP(3),
						closeByALS(4),
						closeByLP(5)
					}
					MAX-ACCESS read-write
					STATUS current
					DESCRIPTION
					"
						远端设备以太网光口的开关使能
					"
					::= { rcftRemoteEthFxPortEntry 9 }

       rcftRemoteEthFxModuleType  OBJECT-TYPE
      	  SYNTAX INTEGER
      	  {
      	     optical-M(1),
      	     optical-S1(2),
      	     optical-S2(3),
      	     optical-S3(4),
      	     optical-SS13(5),
      	     optical-SS15(6),
      	     optical-SS23(7),
      	     optical-SS25(8),
      	     --optical-SS3(9),    kuanglili 20090519 根据公司规范取消ss3光头类型
      	     optical-SS34(9),
      	     optical-SS35(10),
      	     optical-S15(12),   	--kuanglili 20090909 S15光模块的枚举为12
      	     optical-SFP(15),
      	     unknown-type(100)
      	  }
      	  MAX-ACCESS read-only
      	  STATUS current
      	  DESCRIPTION
      	  "
      	    远端设备以太网光口的光模块类型
      	  "
	      ::= { rcftRemoteEthFxPortEntry 10 }

	  rcftRemoteEthFxFaultPass	OBJECT-TYPE
	 		SYNTAX INTEGER
	 		{
	 			enable(1),
	 			disable(2)
	 		}
	 	MAX-ACCESS read-write
	 	STATUS	current
	 	DESCRIPTION
	 	"
	 	远端设备以太网光口故障转移功能(1:使能,2:禁止)
	 	"
		::= { rcftRemoteEthFxPortEntry 11 }

	rcftRemoteEthFxPortLink OBJECT-TYPE
	      SYNTAX  INTEGER
	      		 {
	                 link(1),
	                 unlink(2)
	             }
	      MAX-ACCESS  read-only
	      STATUS  current
	      DESCRIPTION
	      "
	            远端设备光口LINK
	      "

	      ::= { rcftRemoteEthFxPortEntry 12 }

	rcftRemoteEthFxRxToTxFaultPass	OBJECT-TYPE
		SYNTAX	INTEGER
		{
			enable(1),
			disable(2)
		}
	 	MAX-ACCESS read-write
	 	STATUS	current
	 	DESCRIPTION
	 	"
	 		远端设备以太网光口故障返回功能(1:使能,2:禁止)
	 	"
		::= { rcftRemoteEthFxPortEntry 13 }

	rcftRemoteEthFxTxDisabledByFR	OBJECT-TYPE
		SYNTAX	INTEGER
		{
			open(1),
			close(2)
		}
	 	MAX-ACCESS read-only
	 	STATUS	current
	 	DESCRIPTION
	 	"
	 		远端设备以太网光口发送关闭的原因是由于光口接收故障向发送方向转移功能使能造成的。
		"
		::= { rcftRemoteEthFxPortEntry 14 }

		rcftRemoteEthFxOrderTimeParameter OBJECT-TYPE
			SYNTAX	INTEGER
			MAX-ACCESS read-write
			STATUS	current
			DESCRIPTION
	  		 "
	  		    给远端模块以太网光口发送命令时所需要赋的时长参数。

	  		    1: 测试时长1分钟
	  		    2: 测试时长2分钟
	  		    3: 测试时长4分钟
	  		    4: 测试时长8分钟
	  		    5: 测试时长15分钟
	  		    6: 测试时长30分钟
	  		    7: 测试时长60分钟

	  		    18: 测试2帧
	  		    19: 测试5帧
	  		    20: 测试10帧
	  		    21: 测试20帧
	  		    22: 测试50帧
	  		    23: 测试100帧
	  		"
            ::= { rcftRemoteEthFxPortEntry 15 }

      	rcftRemoteEthFxOrderModeParameter OBJECT-TYPE
			SYNTAX	INTEGER
			MAX-ACCESS read-write
			STATUS	current
			DESCRIPTION
	  		 "
	  		    给远端模块以太网光口发送命令时所需要赋的模式参数。

	  		"
            ::= { rcftRemoteEthFxPortEntry 16 }

		rcftRemoteEthFxOrder	OBJECT-TYPE
			SYNTAX	INTEGER
			MAX-ACCESS	read-write
			STATUS	current
			DESCRIPTION
			"
			    1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
				22: 端口BERT测试开始
				23: 端口BERT测试结束
				24: 环回测试（一次完成自动停止）
			"
		   ::= { rcftRemoteEthFxPortEntry 17 }

	rcftRemoteEthFxPortExist 	OBJECT-TYPE
		SYNTAX	INTEGER
		{
			exist(1),
			no-exist(2)
		}
	 	MAX-ACCESS read-only
	 	STATUS	current
	 	DESCRIPTION
	 	"
			光模块是否在位：1：在位，2：不在位
		"
        ::= { rcftRemoteEthFxPortEntry 18 }

	rcftRemoteEthFxPortAuto		OBJECT-TYPE
		SYNTAX	INTEGER
		{
			enable(1),
			disable(2)
		}
	 	MAX-ACCESS read-write
	 	STATUS	current
	 	DESCRIPTION
	 	"
			光口自协商：1：使能，2：禁止
		"
        ::= { rcftRemoteEthFxPortEntry 19 }

	rcftRemoteEthFxModuleMaxSpeed   OBJECT-TYPE
	 	SYNTAX	INTEGER
		{
			stm16(1),
        	stm8(2),
        	stm4(3),
        	stm1(4)

		}
		MAX-ACCESS read-only
	 	STATUS	current
	 	DESCRIPTION
	 	"
			光口最大速率
			1 : 2.5Gbit/s;
       	    2 : 1.25Gbit/s;
       	    3 : 622Mbit/s;
       	    4 : 155Mbit/s;
       	    5 : 125Mbit/s
		"
        ::= { rcftRemoteEthFxPortEntry 20 }

	rcftRemoteEthFxTranDistance		OBJECT-TYPE
		SYNTAX	INTEGER
		MAX-ACCESS read-only
		STATUS	current
		DESCRIPTION
	  	"
	  		传输距离，单位km。

	  	"
        ::= { rcftRemoteEthFxPortEntry 21 }

	rcftRemoteEthFxModuleWaveLen	OBJECT-TYPE
      SYNTAX INTEGER
      MAX-ACCESS read-only
      STATUS current
      DESCRIPTION
      "
       	SFP模块工作波长(单位为nm)
      "
	  ::= { rcftRemoteEthFxPortEntry 22 }

	rcftRemoteEthFxPortConnectorType   OBJECT-TYPE
      SYNTAX INTEGER
      {
        unkkown(1),
        rj45(2),
        sc(3),
        style1(4),
        style2(5),
        bnctnc(6),
        coaheader(7),
        jack(8),
        lc(9),
        mtrj(10),
        mu(11),
        sg(12),
        opticalpigtail(13),
        hssdc2(14),
        copperpigtail(15)

      }
      MAX-ACCESS read-only
      STATUS current
      DESCRIPTION
      "
       	SFP模块连接头类型:(1 : 未知类型;
       	                   2 : rj45;
       	                   3 : sc;
       	                   4 : style1;
       	                   5 : style2;
       	                   6 : bnctnc;
       	                   7 : coaheader;
       	                   8 : jack;
       	                   9 : lc;
       	                   10 : mtrj;
       	                   11 : mu;
       	                   12 : sg;
       	                   13 : opticalpigtail;
       	                   14 : hssdc2;
       	                   15 : copperpigtail)
      "
      ::={rcftRemoteEthFxPortEntry 23}

    rcftRemoteEthFxPortTransmitMedia  OBJECT-TYPE
      SYNTAX INTEGER
      {
        unkkown(1),
        singleMode9um(2),
        multiMode50um(3),
        multiMode62point5um(4),
        copperline(15)
      }
      MAX-ACCESS read-only
      STATUS current
      DESCRIPTION
      "
       	SFP模块传输介质:(1 : 未知类型;
       	                 2 : 单模9um;
       	                 3 : 多模50um;
       	                 4 : 多模62.5um
       	                 15:铜线)
      "
      ::={rcftRemoteEthFxPortEntry 24}

	rcftRemoteEthFxModuleManufacturer	OBJECT-TYPE
      SYNTAX OCTET STRING(SIZE (0..30))
      MAX-ACCESS read-only
      STATUS current
      DESCRIPTION
      "
       SFP模块的模块制造厂商
      "
      ::= { rcftRemoteEthFxPortEntry 25 }

	rcftRemoteEthFxModuleDescr		OBJECT-TYPE
      SYNTAX OCTET STRING(SIZE (0..30))
      MAX-ACCESS read-only
      STATUS current
      DESCRIPTION
      "
        SFP模块的产品型号
      "
      ::= { rcftRemoteEthFxPortEntry 26 }

	rcftRemoteEthFxPortModuleVersion		OBJECT-TYPE
      SYNTAX OCTET STRING(SIZE (0..10))
      MAX-ACCESS read-only
      STATUS current
      DESCRIPTION
      "
        SFP模块的版本号
      "
      ::= { rcftRemoteEthFxPortEntry 27 }

	rcftRemoteEthFxModuleSerialNumber	OBJECT-TYPE
      SYNTAX OCTET STRING(SIZE (0..30))
      MAX-ACCESS read-only
      STATUS current
      DESCRIPTION
      "
        SFP模块的序列号
      "
      ::={rcftRemoteEthFxPortEntry 28}



	rcftRemoteEthFxPortSFPDiagnoInfo	OBJECT-TYPE
  		 SYNTAX	INTEGER
  		 MAX-ACCESS 	read-only
  		 STATUS	current
  		 DESCRIPTION
  		 "
     		光模块数字诊断的相关信息
    		bit3: 监测到sfp模块         1：有告警   0：无
     		bit2: 采用内部校准：  		1：有效，   0：无效
      		bit1: 采用外部校准：  		1：有效，   0：无效
     		bit0: 是否具有数字诊断功能：1：有 		0：无
  		 "
  		 ::={rcftRemoteEthFxPortEntry 29}

	rcftRemoteEthFxSFPDiagnoAlarmStatus	OBJECT-TYPE
  		 SYNTAX	INTEGER
  		 MAX-ACCESS 	read-only
  		 STATUS	current
  		 DESCRIPTION
  		 "
     		光模块数字诊断的相关告警

            bit9: 收光功率下限告警：  	1：有告警，0：没有告警
     		bit8: 收光功率上限告警：  	1：有告警，0：没有告警
     		bit7: 发光功率下限告警：  	1：有告警，0：没有告警
     		bit6: 发光功率上限告警：  	1：有告警，0：没有告警
     		bit5: 电流下限告警：  		1：有告警，0：没有告警
     		bit4: 电流上限告警：  		1：有告警，0：没有告警
     		bit3: 电压下限告警：  		1：有告警，0：没有告警
     		bit2: 电压上限告警：  		1：有告警，0：没有告警
     		bit1: 温度下限告警：  		1：有告警，0：没有告警
     		bit0: 温度上限告警：  		1：有告警，0：没有告警

 	     "
		 ::={rcftRemoteEthFxPortEntry 30}


	rcftRemoteEthFxPortStatus    OBJECT-TYPE
  		 SYNTAX	INTEGER
  		 MAX-ACCESS 	read-write
  		 STATUS	current
  		 DESCRIPTION
  		 "
     		bit1-0：速率。				00：10M，01：100M。
			bit2：双工。				1：全双工。0：半双工
			bit3：发送使能/禁止。		1：使能，0：禁止。
			bit4：远端掉电。			1：正常，0：掉电。
			bit5: ALS 1：使能，0：禁止
			bit6：LBK-Test_Valid。1：环回测试过， 0：没有进行过环回测试
			bit7：LBK-Test-OK（Bit6为1时有效）。1：测试成功，0：测试失败
			bit8：以太网光口OAM网管。			1：使能；  0：禁止。
  		 "
  		 ::={rcftRemoteEthFxPortEntry 31}

       rcftRemoteEthFxUntag   OBJECT-TYPE
  		 SYNTAX	INTEGER
  		 MAX-ACCESS 	read-write
  		 STATUS	current
  		 DESCRIPTION
  		 "
   			 光口的tag
   			 	1：不带tag，
   			 	2：带tag
     	 "
  		 ::={rcftRemoteEthFxPortEntry 32}


		rcftRemoteEthFxPVID   OBJECT-TYPE
  		 SYNTAX	INTEGER
  		 MAX-ACCESS 	read-write
  		 STATUS	current
  		 DESCRIPTION
  		 "
   			 光口的PVID
     	 "
  		 ::={rcftRemoteEthFxPortEntry 33}

    rcftRemoteEthFxPortSFPType    OBJECT-TYPE
  		 SYNTAX	INTEGER
  		 {
 	     	utp(1),
 	     	fiber(2)
 	     }
  		 MAX-ACCESS 	read-only
  		 STATUS	current
  		 DESCRIPTION
  		 "
     		SFP接口类型，1：eth电口，2：eth光口。
         "
         ::={rcftRemoteEthFxPortEntry 34}

   rcftRemoteEthFxPortSFPInfo  OBJECT-TYPE
  		 SYNTAX	INTEGER
  		 MAX-ACCESS 	read-only
  		 STATUS	current
  		 DESCRIPTION
  		 "
			Bit2：远端SFP模块光口打开使能：		1：打开，0：关闭
			Bit1：远端SFP模块激光器发送失效：	1：正常，0：失效
			Bit0：远端SFP模块输入信号丢失： 	1：正常，0：丢失
 	  	 "
  		 ::={rcftRemoteEthFxPortEntry 35}

     rcftRemoteEthFxPortLoopStatus   OBJECT-TYPE
  		 SYNTAX	INTEGER
  		 MAX-ACCESS 	read-only
  		 STATUS	current
  		 DESCRIPTION
  		 "
			光口环回:
            	1: 光口本地外环
            	2：光口远端外环
           		3：光口本地内环
            	4：OAM环

            	100:正常
 	  	 "
  		 ::={rcftRemoteEthFxPortEntry 36}

  	 rcftRemoteEthFxPortRxRestrictSpeed    OBJECT-TYPE
  		 SYNTAX	INTEGER
  		 MAX-ACCESS 	read-write
  		 STATUS	current
  		 DESCRIPTION
  		 "
			ethfx 光口 接收带宽限制
 	  	 "
  		 ::={rcftRemoteEthFxPortEntry 37}

  	 rcftRemoteEthFxPortTxRestrictSpeed    OBJECT-TYPE
  		 SYNTAX	INTEGER
  		 MAX-ACCESS 	read-write
  		 STATUS	current
  		 DESCRIPTION
  		 "
			ethfx 光口 发送带宽限制
 	  	 "
  		 ::={rcftRemoteEthFxPortEntry 38}

  		rcftRemoteEthFxSFPDiagnoWarningStatus	OBJECT-TYPE
  		 SYNTAX	INTEGER
  		 MAX-ACCESS 	read-only
  		 STATUS	current
  		 DESCRIPTION
  		 "
     		光模块数字诊断的相关预警

            bit9: 收光功率下限预警：  	1：有预警，0：没有预警
     		bit8: 收光功率上限预警：  	1：有预警，0：没有预警
     		bit7: 发光功率下限预警：  	1：有预警，0：没有预警
     		bit6: 发光功率上限预警：  	1：有预警，0：没有预警
     		bit5: 电流下限预警：  		1：有预警，0：没有预警
     		bit4: 电流上限预警：  		1：有预警，0：没有预警
     		bit3: 电压下限预警：  		1：有预警，0：没有预警
     		bit2: 电压上限预警：  		1：有预警，0：没有预警
     		bit1: 温度下限预警：  		1：有预警，0：没有预警
     		bit0: 温度上限预警：  		1：有预警，0：没有预警

 	     "
		 ::={rcftRemoteEthFxPortEntry 39}

  		rcftRemoteEthFxPortLineOrClient	OBJECT-TYPE
  		 SYNTAX	INTEGER
  		 MAX-ACCESS 	read-only
  		 STATUS	current
  		 DESCRIPTION
  		 "
     		远端光口(sfp)属性:
     		1: 线路侧；2：客户测；

 	     "
		 ::={rcftRemoteEthFxPortEntry 40}

       rcftRemoteEthFxCOS    OBJECT-TYPE
  		 SYNTAX	INTEGER
  		 MAX-ACCESS 	read-write
  		 STATUS	current
  		 DESCRIPTION
  		 "
     		0~7
 	     "
		 ::={rcftRemoteEthFxPortEntry 41}



      rcftRemoteEthFxStatisticTable OBJECT-TYPE
	        SYNTAX SEQUENCE OF RcftRemoteEthFxStatisticEntry
	        MAX-ACCESS not-accessible
	        STATUS current
	        DESCRIPTION
	          "
	          远端设备Eth端口的统计表.
	          "
            ::= {rcftRemoteDeviceEthFxObjects 2}

	    rcftRemoteEthFxStatisticEntry OBJECT-TYPE
	        SYNTAX RcftRemoteEthFxStatisticEntry
	        MAX-ACCESS not-accessible
	        STATUS current
	        DESCRIPTION
	          "
	             以rcftRemoteEthFxIndex为索引
	          "
	        AUGMENTS { rcftRemoteEthFxPortEntry }
	        ::= {rcftRemoteEthFxStatisticTable 1}

	    RcftRemoteEthFxStatisticEntry ::= SEQUENCE {

				rcftRemoteEthFxTxPackets         Counter32,
				rcftRemoteEthFxTxBytes           Counter32,
				rcftRemoteEthFxRxPackets         Counter32,
				rcftRemoteEthFxRxBytes           Counter32,
				rcftRemoteEthFxRxLostPackets     Counter32,
				rcftRemoteEthFxFluxTimer		 Counter32,
				rcftRemoteEthFxTxLostPackets     Counter32,
				rcftRemoteEthFx64TxBytes         Counter64,
				rcftRemoteEthFx64RxBytes         Counter64


	         }


    	  rcftRemoteEthFxTxPackets OBJECT-TYPE
					SYNTAX Counter32
					MAX-ACCESS read-only
					STATUS current
					DESCRIPTION
						"
							以太网口发送以太网包数
						"
					::= { rcftRemoteEthFxStatisticEntry 1 }

		 rcftRemoteEthFxTxBytes OBJECT-TYPE
					SYNTAX Counter32
					MAX-ACCESS read-only
					STATUS current
					DESCRIPTION
						"
							以太网口发送以太网字节数
						"
					::= { rcftRemoteEthFxStatisticEntry 2 }

		 rcftRemoteEthFxRxPackets OBJECT-TYPE
					SYNTAX Counter32
					MAX-ACCESS read-only
					STATUS current
					DESCRIPTION
						"
							以太网口接收以太网包数
						"
					::= { rcftRemoteEthFxStatisticEntry 3 }

		 rcftRemoteEthFxRxBytes OBJECT-TYPE
					SYNTAX Counter32
					MAX-ACCESS read-only
					STATUS current
					DESCRIPTION
						"
							以太网口接收以太网字节数
						"
					::= { rcftRemoteEthFxStatisticEntry 4 }

	    rcftRemoteEthFxRxLostPackets OBJECT-TYPE
					SYNTAX Counter32
					MAX-ACCESS read-only
					STATUS current
					DESCRIPTION
						"
							以太网电口接收以太网丢包数
						"
					::= { rcftRemoteEthFxStatisticEntry 5 }

        rcftRemoteEthFxFluxTimer	OBJECT-TYPE
        			SYNTAX		Counter32
        			MAX-ACCESS 	read-only
        			STATUS		current
        			DESCRIPTION
        				"
        					流量统计的时间
        				"
                    ::= { rcftRemoteEthFxStatisticEntry 6 }

	    rcftRemoteEthFxTxLostPackets OBJECT-TYPE
					SYNTAX Counter32
					MAX-ACCESS read-only
					STATUS current
					DESCRIPTION
						"
							以太网电口发送以太网丢包数
						"
					::= { rcftRemoteEthFxStatisticEntry 7 }

		 rcftRemoteEthFx64TxBytes OBJECT-TYPE
					SYNTAX Counter64
					MAX-ACCESS read-only
					STATUS current
					DESCRIPTION
						"
							以太网口发送以太网字节数, 范围 0 至 2 的64次方-1
						"
					::= { rcftRemoteEthFxStatisticEntry 8 }

		 rcftRemoteEthFx64RxBytes OBJECT-TYPE
					SYNTAX Counter64
					MAX-ACCESS read-only
					STATUS current
					DESCRIPTION
						"
							以太网口接收以太网字节数, 范围 0 至 2 的64次方-1
						"
					::= { rcftRemoteEthFxStatisticEntry 9 }


       rcftRemoteEthFxPortCurrentTable OBJECT-TYPE
              SYNTAX  SEQUENCE OF RcftRemoteEthFxPortCurrentEntry
              MAX-ACCESS  not-accessible
              STATUS  current
              DESCRIPTION
                 "
                 The Remote Device FX Port table.
                 "
             ::= { rcftRemoteDeviceEthFxPerformance 1 }

   		rcftRemoteEthFxPortCurrentEntry OBJECT-TYPE
              SYNTAX  RcftRemoteEthFxPortCurrentEntry
              MAX-ACCESS  not-accessible
              STATUS  current
              DESCRIPTION
                 "
                 An entry in the Fx Port config table.

                 "
              INDEX   { rcftChassisIndex, rcftSlotIndex,rcftRemoteDeviceIndex, rcftRemoteEthFxIndex }
             ::= { rcftRemoteEthFxPortCurrentTable 1 }

          RcftRemoteEthFxPortCurrentEntry ::=
              SEQUENCE {
		            rcftRemoteEthFxCurrentTemperature	OCTET STRING,
		            rcftRemoteEthFxCurrentVoltage       OCTET STRING,
		            rcftRemoteEthFxCurrentOffsetCurr    OCTET STRING,
		            rcftRemoteEthFxCurrentRecvPower     OCTET STRING,
		            rcftRemoteEthFxCurrentSendPower     OCTET STRING
                   }

	      rcftRemoteEthFxCurrentTemperature OBJECT-TYPE
	            SYNTAX  OCTET STRING(SIZE (0..20))
	            MAX-ACCESS  read-only
	            STATUS  current
	            DESCRIPTION
	               "this OBJECT indicates the average temperature in the current 15 minute interval."
	             ::= { rcftRemoteEthFxPortCurrentEntry 1 }

	      rcftRemoteEthFxCurrentVoltage OBJECT-TYPE
	            SYNTAX  OCTET STRING(SIZE (0..20))
	            MAX-ACCESS  read-only
	            STATUS  current
	            DESCRIPTION
	               "This OBJECT indicates the averaget voltage in the current 15 minute interval."
	             ::= { rcftRemoteEthFxPortCurrentEntry 2 }

	      rcftRemoteEthFxCurrentOffsetCurr OBJECT-TYPE
	            SYNTAX  OCTET STRING(SIZE (0..20))
	            MAX-ACCESS  read-only
	            STATUS  current
	            DESCRIPTION
	               "The object indicates the average offset current in the current
	               15 minute interval."
	            ::= { rcftRemoteEthFxPortCurrentEntry 3 }

	      rcftRemoteEthFxCurrentRecvPower OBJECT-TYPE
	            SYNTAX  OCTET STRING(SIZE (0..20))
	            MAX-ACCESS  read-only
	            STATUS  current
	            DESCRIPTION
	               "This object indicates the average receive power in the current
	               15 minute interval."
	            ::= { rcftRemoteEthFxPortCurrentEntry 4 }

	      rcftRemoteEthFxCurrentSendPower OBJECT-TYPE
	            SYNTAX  OCTET STRING(SIZE (0..20))
	            MAX-ACCESS  read-only
	            STATUS  current
	            DESCRIPTION
	               "This object indicates the average send power in the current
	               15 minute interval."
	              ::= { rcftRemoteEthFxPortCurrentEntry 5 }



       rcftRemoteEthFxPortIntervalTable OBJECT-TYPE
              SYNTAX  SEQUENCE OF RcftRemoteEthFxPortIntervalEntry
              MAX-ACCESS  not-accessible
              STATUS  current
              DESCRIPTION
                 "
                 The Remote Device FX Port table.
                 "
             ::= { rcftRemoteDeviceEthFxPerformance 2 }

   		rcftRemoteEthFxPortIntervalEntry OBJECT-TYPE
              SYNTAX  RcftRemoteEthFxPortIntervalEntry
              MAX-ACCESS  not-accessible
              STATUS  current
              DESCRIPTION
                 "
                 An entry in the Fx Port config table.

                 "
              INDEX   { rcftChassisIndex, rcftSlotIndex,rcftRemoteDeviceIndex
              			, rcftRemoteEthFxIndex, rcftRemoteEthFxIntervalNumber }
             ::= { rcftRemoteEthFxPortIntervalTable 1 }

          RcftRemoteEthFxPortIntervalEntry ::=
              SEQUENCE {
	           	    rcftRemoteEthFxIntervalNumber 			INTEGER,
	                rcftRemoteEthFxIntervalTemperature	 	OCTET STRING,
	                rcftRemoteEthFxIntervalVoltage      	OCTET STRING,
	                rcftRemoteEthFxIntervalOffsetCurr   	OCTET STRING,
	                rcftRemoteEthFxIntervalRecvPower    	OCTET STRING,
	                rcftRemoteEthFxIntervalSendPower    	OCTET STRING
                   }

		  rcftRemoteEthFxIntervalNumber OBJECT-TYPE
		 		SYNTAX INTEGER
		 		MAX-ACCESS  read-only
		 		STATUS current
		 		DESCRIPTION
		 		"
		 			WAN FX PORT 第几个十五分钟
		 		"
		 		::= { rcftRemoteEthFxPortIntervalEntry 1 }


	      rcftRemoteEthFxIntervalTemperature OBJECT-TYPE
	            SYNTAX  OCTET STRING(SIZE (0..20))
	            MAX-ACCESS  read-only
	            STATUS  current
	            DESCRIPTION
	               "this OBJECT indicates the average temperature in the interval 15 minute interval."
	             ::= { rcftRemoteEthFxPortIntervalEntry 2 }

	      rcftRemoteEthFxIntervalVoltage OBJECT-TYPE
	            SYNTAX  OCTET STRING(SIZE (0..20))
	            MAX-ACCESS  read-only
	            STATUS  current
	            DESCRIPTION
	               "This OBJECT indicates the averaget voltage in the interval 15 minute interval."
	             ::= { rcftRemoteEthFxPortIntervalEntry 3 }

	      rcftRemoteEthFxIntervalOffsetCurr OBJECT-TYPE
	            SYNTAX  OCTET STRING(SIZE (0..20))
	            MAX-ACCESS  read-only
	            STATUS  current
	            DESCRIPTION
	               "The object indicates the average offset interval in the interval
	               15 minute interval."
	            ::= { rcftRemoteEthFxPortIntervalEntry 4 }

	      rcftRemoteEthFxIntervalRecvPower OBJECT-TYPE
	            SYNTAX  OCTET STRING(SIZE (0..20))
	            MAX-ACCESS  read-only
	            STATUS  current
	            DESCRIPTION
	               "This object indicates the average receive power in the current
	               15 minute interval."
	            ::= { rcftRemoteEthFxPortIntervalEntry 5 }

	      rcftRemoteEthFxIntervalSendPower OBJECT-TYPE
	            SYNTAX  OCTET STRING(SIZE (0..20))
	            MAX-ACCESS  read-only
	            STATUS  current
	            DESCRIPTION
	               "This object indicates the average send power in the current
	               15 minute interval."
	            ::= { rcftRemoteEthFxPortIntervalEntry 6 }

       rcftRemoteEthFxPortPerTable OBJECT-TYPE
              SYNTAX  SEQUENCE OF RcftRemoteEthFxPortPerEntry
              MAX-ACCESS  not-accessible
              STATUS  current
              DESCRIPTION
                 "
                 The Remote Device FX Port table.
                 "
             ::= { rcftRemoteDeviceEthFxPerformance 3 }

   		rcftRemoteEthFxPortPerEntry OBJECT-TYPE
              SYNTAX  RcftRemoteEthFxPortPerEntry
              MAX-ACCESS  not-accessible
              STATUS  current
              DESCRIPTION
                 "
                 An entry in the Fx Port config table.

                 "
              INDEX   { rcftChassisIndex, rcftSlotIndex,rcftRemoteDeviceIndex, rcftRemoteEthFxIndex }
             ::= { rcftRemoteEthFxPortPerTable 1 }

          RcftRemoteEthFxPortPerEntry ::=
              SEQUENCE {
	                rcftRemoteEthFxPortPerTemperature	  OCTET STRING,
	                rcftRemoteEthFxPortPerVoltage       OCTET STRING,
	                rcftRemoteEthFxPortPerOffsetCurr    OCTET STRING,
	                rcftRemoteEthFxPortPerRecvPower     OCTET STRING,
	                rcftRemoteEthFxPortPerSendPower     OCTET STRING

                   }

	      rcftRemoteEthFxPortPerTemperature OBJECT-TYPE
	            SYNTAX  OCTET STRING(SIZE (0..20))
	            MAX-ACCESS  read-only
	            STATUS  current
	            DESCRIPTION
	               "this OBJECT indicates the average temperature at present."
	             ::= { rcftRemoteEthFxPortPerEntry 1 }

	      rcftRemoteEthFxPortPerVoltage OBJECT-TYPE
	            SYNTAX  OCTET STRING(SIZE (0..20))
	            MAX-ACCESS  read-only
	            STATUS  current
	            DESCRIPTION
	               "This OBJECT indicates the averaget voltage at present."
	             ::= { rcftRemoteEthFxPortPerEntry 2 }

	      rcftRemoteEthFxPortPerOffsetCurr OBJECT-TYPE
	            SYNTAX  OCTET STRING(SIZE (0..20))
	            MAX-ACCESS  read-only
	            STATUS  current
	            DESCRIPTION
	               "The object indicates the average offset current at present."
	            ::= { rcftRemoteEthFxPortPerEntry 3 }

	      rcftRemoteEthFxPortPerRecvPower OBJECT-TYPE
	            SYNTAX  OCTET STRING(SIZE (0..20))
	            MAX-ACCESS  read-only
	            STATUS  current
	            DESCRIPTION
	               "This object indicates the average receive power at present."
	            ::= { rcftRemoteEthFxPortPerEntry 4 }

	      rcftRemoteEthFxPortPerSendPower OBJECT-TYPE
	            SYNTAX  OCTET STRING(SIZE (0..20))
	            MAX-ACCESS  read-only
	            STATUS  current
	            DESCRIPTION
	               "This object indicates the average send power at present."
	              ::= { rcftRemoteEthFxPortPerEntry 5 }


      rcftRemoteEthFeStatisticTable OBJECT-TYPE
	        SYNTAX SEQUENCE OF RcftRemoteEthFeStatisticEntry
	        MAX-ACCESS not-accessible
	        STATUS current
	        DESCRIPTION
	          "
	          远端设备Eth端口的统计表.
	          "
            ::= {rcftRemoteDeviceEthFeObjects 2}

	    rcftRemoteEthFeStatisticEntry OBJECT-TYPE
	        SYNTAX RcftRemoteEthFeStatisticEntry
	        MAX-ACCESS not-accessible
	        STATUS current
	        DESCRIPTION
	          "
	             以rcftRemoteEthFeIndex为索引
	          "
	        AUGMENTS { rcftRemoteEthFePortEntry }
	        ::= {rcftRemoteEthFeStatisticTable 1}

	    RcftRemoteEthFeStatisticEntry ::= SEQUENCE {

				rcftRemoteEthFeTxPackets         Counter32,
				rcftRemoteEthFeTxBytes           Counter32,
				rcftRemoteEthFeRxPackets         Counter32,
				rcftRemoteEthFeRxBytes           Counter32,
				rcftRemoteEthFeRxLostPackets     Counter32,
				rcftRemoteEthFeFluxTimer		 Counter32,
				rcftRemoteEthFeTxLostPackets     Counter32
	         }


    	  rcftRemoteEthFeTxPackets OBJECT-TYPE
					SYNTAX Counter32
					MAX-ACCESS read-only
					STATUS current
					DESCRIPTION
						"
							以太网口发送以太网包数
						"
					::= { rcftRemoteEthFeStatisticEntry 1 }

		 rcftRemoteEthFeTxBytes OBJECT-TYPE
					SYNTAX Counter32
					MAX-ACCESS read-only
					STATUS current
					DESCRIPTION
						"
							以太网口发送以太网字节数
						"
					::= { rcftRemoteEthFeStatisticEntry 2 }

		 rcftRemoteEthFeRxPackets OBJECT-TYPE
					SYNTAX Counter32
					MAX-ACCESS read-only
					STATUS current
					DESCRIPTION
						"
							以太网口接收以太网包数
						"
					::= { rcftRemoteEthFeStatisticEntry 3 }

		 rcftRemoteEthFeRxBytes OBJECT-TYPE
					SYNTAX Counter32
					MAX-ACCESS read-only
					STATUS current
					DESCRIPTION
						"
							以太网口接收以太网字节数
						"
					::= { rcftRemoteEthFeStatisticEntry 4 }

	    rcftRemoteEthFeRxLostPackets OBJECT-TYPE
					SYNTAX Counter32
					MAX-ACCESS read-only
					STATUS current
					DESCRIPTION
						"
							以太网电口接收以太网丢包数
						"
					::= { rcftRemoteEthFeStatisticEntry 5 }

        rcftRemoteEthFeFluxTimer	OBJECT-TYPE
        			SYNTAX		Counter32
        			MAX-ACCESS 	read-only
        			STATUS		current
        			DESCRIPTION
        				"
        					流量统计的时间
        				"
                    ::= { rcftRemoteEthFeStatisticEntry 6 }

	    rcftRemoteEthFeTxLostPackets OBJECT-TYPE
					SYNTAX Counter32
					MAX-ACCESS read-only
					STATUS current
					DESCRIPTION
						"
							以太网电口发送以太网丢包数
						"
					::= { rcftRemoteEthFeStatisticEntry 7 }

	     rcftRemoteEthFePortConfTable OBJECT-TYPE
              SYNTAX  SEQUENCE OF RcftRemoteEthFePortConfEntry
              MAX-ACCESS  not-accessible
              STATUS  current
              DESCRIPTION
              "
                 The Remote Device Fe Port config table.
              "
             ::= { rcftRemoteDeviceEthFeObjects 3 }

   		rcftRemoteEthFePortConfEntry OBJECT-TYPE
              SYNTAX  RcftRemoteEthFePortConfEntry
              MAX-ACCESS  not-accessible
              STATUS  current
              DESCRIPTION
              "
                 An entry in the Fe Port config table.
              "
              INDEX   { rcftChassisIndex, rcftSlotIndex,rcftRemoteDeviceIndex,  rcftRemoteEthFeIndex }
             ::= { rcftRemoteEthFePortConfTable 1 }

        RcftRemoteEthFePortConfEntry ::=
          	  SEQUENCE {
          			    rcftRemoteEthFeConfSpeed       INTEGER,
						rcftRemoteEthFeConfDuplex      INTEGER
					}

		 rcftRemoteEthFeConfSpeed OBJECT-TYPE
		       SYNTAX INTEGER
		        {
		            rcft10Mbps(1),
		            rcft100Mbps(2),
		            rcft1000Mbps(3),
		            rcft10Gbps(4),
		            other(16)
		        }
		        MAX-ACCESS read-write
		        STATUS current
		        DESCRIPTION
		          "
		            远端设备电口的速率配置信息.
		            The speed of the electronic port.
		            1、10Mbps
		            2、100Mbps
		            3、1000Mbps
		            4、10Gbps
		            5、other
		          "
		          ::= { rcftRemoteEthFePortConfEntry 1 }


		 rcftRemoteEthFeConfDuplex OBJECT-TYPE
		        SYNTAX INTEGER
		        {
		            full-duplex(1),
		            half-duplex(2)
		        }
		        MAX-ACCESS read-write
		        STATUS current
		        DESCRIPTION
		          "
		          远端设备电口双工模式配置信息（1:全双工，2:半双工）.
		          The duplex mode of the electronic port.
		          1:full duplex
		          2:half duplex
		          "
		         ::= { rcftRemoteEthFePortConfEntry 2 }
----------------------------------------------------------------------------
------------------Remote Device E1 table
----------------------------------------------------------------------------


        rcftRemoteDeviceE1Table OBJECT-TYPE
              SYNTAX  SEQUENCE OF RcftRemoteDeviceE1Entry
              MAX-ACCESS  not-accessible
              STATUS  current
              DESCRIPTION
                 "
                 The Remote Device System table.
                 "
             ::= { rcftRemoteDeviceE1Objects 1 }

   		rcftRemoteDeviceE1Entry OBJECT-TYPE
              SYNTAX  RcftRemoteDeviceE1Entry
              MAX-ACCESS  not-accessible
              STATUS  current
              DESCRIPTION
                 "
                 An entry in the E1 config table.
                 索引使用对应的VC12的ifIndex
                 "
              INDEX   { rcftChassisIndex, rcftSlotIndex,rcftRemoteDeviceIndex,rcftRemoteE1Index }
             ::= { rcftRemoteDeviceE1Table 1 }

          RcftRemoteDeviceE1Entry ::=
              SEQUENCE {
              			rcftRemoteE1Index					Integer32,
          			    rcftRemoteE1BertEnable            	INTEGER,
						rcftRemoteE1ClockMode             	INTEGER,
          			    rcftRemoteE1FrameEnable			  	INTEGER,
          			    rcftRemoteE1AlarmStatus			  	INTEGER,
          			    rcftRemoteE1SubSpeed              	Unsigned32,
          			    rcftRemoteE1CRCDetectEnable		  	INTEGER,
          			    rcftRemoteE1ErrCodeSecCnt         	Counter32,
          			    rcftRemoteE1SErrCodeSecCnt        	Counter32,
          			    rcftRemoteE1TransErrorCode		  	INTEGER,
          			    rcftRemoteE1CRCStatus				INTEGER,
          			    rcftRemoteE1FaultPass				INTEGER,
          			    rcftRemoteE1LocalLoopEn				INTEGER,
          			    rcftRemoteE1Location				INTEGER,
                   		rcftRemoteE1FoundLink		       	INTEGER,
                   		rcftRemoteE1UnUsed		            INTEGER,
                   		rcftRemoteToLocalE1AlarmStatus		INTEGER,
                   		rcftRemoteE1Balance					INTEGER,
                   		rcftRemoteE1PortStatus				INTEGER,
                   		rcftRemoteE1PortTS0Mode				INTEGER,
                   		rcftRemoteE1PortIdleCode			INTEGER,
                   		rcftRemoteE1LoopStatus				INTEGER,
						rcftRemoteE1OrderTimeParameter		INTEGER,
						rcftRemoteE1OrderModeParameter		INTEGER,
						rcftRemoteE1Order					INTEGER,
						rcftRemoteE1PortType				INTEGER,
						rcftRemoteE1BertStatus				INTEGER,
						rcftRemoteE1BertTime				Unsigned32,
						rcftRemoteE1BertErrCode				Unsigned32,
						rcftRemoteE1BertUnusedTime			Unsigned32,
						rcftRemoteE1BertPortSpeed			Unsigned32,
						rcftRemoteE1BertCodeType			INTEGER,
						rcftRemoteE1BertCodeNum				INTEGER,
                   		rcftRemoteE1LoopSwitchStatus		INTEGER,
                   		rcftRemoteE1AlarmRejest		INTEGER,
                   		rcftRemoteT1AlarmStatus	  INTEGER,
                   		rcftRemoteE1PortVCGNumber	INTEGER,
                   		rcftRemoteE1ToLNumber	INTEGER,
                   		rcftRemoteE1CVCnt		INTEGER
                   }

         rcftRemoteE1Index OBJECT-TYPE
            SYNTAX      Integer32
            MAX-ACCESS  read-only
            STATUS      current
            DESCRIPTION
            "
          	  远端设备索引
            "
            ::= { rcftRemoteDeviceE1Entry 1 }

        rcftRemoteE1BertEnable OBJECT-TYPE
          SYNTAX  INTEGER {
                    enable (1),
                    disable (2)
                    }
          MAX-ACCESS  read-write
          STATUS  current
          DESCRIPTION
             "
               远端设备E1误码仪功能
             "
		  ::= { rcftRemoteDeviceE1Entry 2}


       rcftRemoteE1ClockMode	OBJECT-TYPE
       		SYNTAX INTEGER{
       		         master(1),
       		         secondary(2),
       		         transparent(3),
       		         e1received(4)
       		}
          MAX-ACCESS  read-write
          STATUS  current
          DESCRIPTION
             "
               远端设备E1的时钟模式      1:主	2：从	3：透传   4：E1接收
             "
		  ::= { rcftRemoteDeviceE1Entry 3}


       rcftRemoteE1FrameEnable 		OBJECT-TYPE
       		SYNTAX INTEGER
	        {
	              transparent(1),
	    	      pcm(2)
	        }
	        MAX-ACCESS read-write
	        STATUS current
	        DESCRIPTION
	          "
	          	远端设备E1口工作模式：（1：透明方式，2：成帧方式）.
	          "
             ::= { rcftRemoteDeviceE1Entry 4}

      rcftRemoteE1AlarmStatus		OBJECT-TYPE
      		SYNTAX	INTEGER
      		MAX-ACCESS		read-only
      		STATUS			current
      		DESCRIPTION
      			"
      				远端设备E1端口的告警信息
      				--------------------------------------------------------------
				    | Bit15 | Bit14 | Bit13 | Bit12 | Bit11 | Bit10 |Bit9 | Bit8 |
				    --------------------------------------------------------------
				    ---------------------------------------------------------
				    | Bit7 | Bit6 | Bit5 | Bit4 | Bit3 | Bit2 | Bit1 | Bit0 |
				    ---------------------------------------------------------
				     bit0:receive signal LOS
				     bit1:receive signal AIS
				     bit2:receive signal LOF
				     bit3:receive signal CRC
				     bit4:receive signal LOMF
				     bit5:receive signal CV
				     bit6:  TSD

				     bit16:receive signal RLOS
				     bit17:receive signal RAIS
				     bit19:receive signal RLOF
				     bit21:receive signal RCRC

				     每一位：0：告警，1：正常
      			"
            ::= { rcftRemoteDeviceE1Entry 5}


     	rcftRemoteE1SubSpeed   OBJECT-TYPE
     			SYNTAX Unsigned32
     			MAX-ACCESS	read-write
          		STATUS  current
          		DESCRIPTION
               	"
                 	设置成帧E1的子速率
                 	每一比特代表相应的时隙
               	"
          	::= { rcftRemoteDeviceE1Entry 6}


		  rcftRemoteE1CRCDetectEnable  OBJECT-TYPE
	          SYNTAX  INTEGER {
	                    enable (1),
	                    disable (2)
	                    }
	          MAX-ACCESS  read-write
	          STATUS  current
	          DESCRIPTION
	                 "
	                 	远端设备E1端口CRC自适应(1:使能，2:禁止)
	                 "
			  ::= { rcftRemoteDeviceE1Entry 7 }


		 rcftRemoteE1ErrCodeSecCnt  OBJECT-TYPE
		 		SYNTAX 		Counter32
		 		MAX-ACCESS	read-only
		 		STATUS		current
		 	    DESCRIPTION
		 	    		"
		 	    			远端设备E1端口的误码秒计数
		 	    		"
		 	    ::= { rcftRemoteDeviceE1Entry 8 }


		 rcftRemoteE1SErrCodeSecCnt  OBJECT-TYPE
		 		SYNTAX 		Counter32
		 		MAX-ACCESS	read-only
		 		STATUS		current
		 	    DESCRIPTION
		 	    		"
		 	    			远端设备E1端口的严重误码秒计数
		 	    		"
		 	    ::= { rcftRemoteDeviceE1Entry 9 }


        rcftRemoteE1TransErrorCode OBJECT-TYPE
        		SYNTAX INTEGER
		    	{
		    	   less10E-6(1),
		    	   more10E-6(2),
		    	   more10E-3(3)
		    	}
		    	MAX-ACCESS read-only
		    	STATUS current
		    	DESCRIPTION
		    	   "
		    	  	远端设备E1传输误码率(1:小于10E-6,2:大于10E-6,小于10E-3,3:大于10E-3).
		    	   "
              ::= { rcftRemoteDeviceE1Entry 10 }

        rcftRemoteE1CRCStatus	OBJECT-TYPE
        	  SYNTAX INTEGER
        	  {
        	       enable(1),
        	       disable(2)
        	  }
		      MAX-ACCESS read-only
		      STATUS current
		      DESCRIPTION
		      	"
		      		远端设备E1端口CRC状态
		      	"
			 ::= { rcftRemoteDeviceE1Entry 11 }

	  rcftRemoteE1FaultPass	  OBJECT-TYPE
	  		SYNTAX	INTEGER
	  		{
	  			enable(1),
	  			disable(2)
	  		}
	  		MAX-ACCESS	read-write
	  		STATUS		current
	  		DESCRIPTION
	  		"
	  			远端设备E1端口故障转移功能(1:使能,2:禁止)
	  		"
			::= { rcftRemoteDeviceE1Entry 12 }

       rcftRemoteE1LocalLoopEn  OBJECT-TYPE
           SYNTAX INTEGER
           {
               enable(1),
               disable(2)
           }
           MAX-ACCESS  read-only
           STATUS      current
           DESCRIPTION
           "
             	远端E1口工作在外环:(1:使能,2:不使能)
           "
           ::= { rcftRemoteDeviceE1Entry 13 }

       rcftRemoteE1Location  OBJECT-TYPE
           SYNTAX INTEGER
    	   {
    	       e1-1(1),
    	       e1-2(2),
    	       e1-3(3),
    	       e1-4(4),
    	       e1-5(5),
    	       e1-6(6),
    	       e1-7(7),
    	       e1-8(8),
    	       unknown(100)
    	   }
    	   MAX-ACCESS  read-write
    	   STATUS      current
    	   DESCRIPTION
    	   "
    	  	远端对应的远端是第几路E1口(1:E1-1,2:E1-2,3:E1-3,4:E1-4).
    	   "
           ::= { rcftRemoteDeviceE1Entry 14 }

       rcftRemoteE1FoundLink OBJECT-TYPE
            SYNTAX INTEGER
            {
                success(1),
                failForDelay(2),
                failForOtherReason(100)
            }
            MAX-ACCESS  read-only
            STATUS      current
        	DESCRIPTION
         	 "
          		远端接口是否建链成功:(1:成功,2:失败)
         	 "
         ::= { rcftRemoteDeviceE1Entry 15 }

       rcftRemoteE1UnUsed OBJECT-TYPE
            SYNTAX INTEGER
            {
                 unused(1),
                 used(2)
            }
            MAX-ACCESS read-write
            STATUS current
            DESCRIPTION
             "
             	远端接口是否被使用:(1:没有,2:有)
             "
         ::= { rcftRemoteDeviceE1Entry 16 }

      rcftRemoteToLocalE1AlarmStatus OBJECT-TYPE
      		SYNTAX	INTEGER
      		MAX-ACCESS		read-only
      		STATUS			current
      		DESCRIPTION
      			"
      				远端设备E1端口所接对端E1端口的告警信息
      				--------------------------------------------------------------
				    | Bit15 | Bit14 | Bit13 | Bit12 | Bit11 | Bit10 |Bit9 | Bit8 |
				    --------------------------------------------------------------
				    ---------------------------------------------------------
				    | Bit7 | Bit6 | Bit5 | Bit4 | Bit3 | Bit2 | Bit1 | Bit0 |
				    ---------------------------------------------------------
				     bit0:receive signal LOS
				     bit1:receive signal AIS
				     bit2:receive signal LOF
				     bit3:receive signal CRC
				     bit4:receive signal LOMF
				     bit5:receive signal CV
				     bit6: TSD, 信号恶化告警
				     bit7：RDI，对端缺陷告警。

					 bit16：对端LOS
					 bit17：对端AIS
				 	 bit19：对端LOF
					 bit20：对端LOMF
					 bit21：对端CRC
					 bit22：对端TSD

				     每一位：0:告警，1：正常
      			"
		::= { rcftRemoteDeviceE1Entry 17 }

		rcftRemoteE1Balance OBJECT-TYPE
			SYNTAX INTEGER
			{
				balance(1),
				imbalance(2)
			}
      		MAX-ACCESS		read-only
      		STATUS			current
      		DESCRIPTION
			"
				远端设备某一路E1的平衡标识
			"
		::= { rcftRemoteDeviceE1Entry 18 }


		rcftRemoteE1PortStatus	OBJECT-TYPE
			SYNTAX	INTEGER
			MAX-ACCESS	read-write
			STATUS		current
			DESCRIPTION
			"
				BIT22 	网管通道模式（可与BIT19组合）     1：启用独立时隙；0：未启用独立时隙
				BIT21	E1环回检测结果	 0：无环   1：有环
				BIT20	E1环回检测		 0: 禁止	   1：使能

				BIT19    SABIT	  0：本地E1 未使用SA BIT； 1：本地E1 使用SA BIT；
				BIT18    E1协议版本       0：V2         1：V3     （网管不显示）
				BIT17	 响应对端跟随	  0：禁止		1：使能
				BIT16	 对端跟随         0：无请求，	1：请求	，对端有请求后，E1时隙网管不可配
			    BIT14	 E1used:     1：E1口被使用； 0：E1口未被使用。
			    BIT13	 CRC_EN:     1：CRC使能； 0：CRC禁止。
				BIT12-11 IN_LBK-Test 00：没有进行过内环测试； 01：保留；10：内环测试成功；11：内环测试失败。
				BIT10-9  EX_LBK-Test 00：没有进行过环回测试； 01：保留；10：外环测试成功；11：外环测试失败。
				BIT8     IDLE_MODE	0：固定使用IDLE_CODE；  1：返回。
				BIT7-6	 Port_En 00：端口开；01：端口关；1x：保留。
				BIT5-4	 阻抗	00：75欧姆非平衡；01：120欧姆平衡；其它：保留。
				BIT3-2	 保留	固定00'b。
				BIT1-0	 接口方式00：BNC； 01：RJ45插座；其它：保留。

			"
		::= { rcftRemoteDeviceE1Entry 19 }

		rcftRemoteE1PortTS0Mode OBJECT-TYPE
			SYNTAX	INTEGER
			MAX-ACCESS	read-write
			STATUS		current
			DESCRIPTION
			"
				工作模式（TS0）：
				8：工作于透明模式，透传TS0-32，TS0=1；
				1：成帧模式0，发送端不发送TS0、接收端重新计算整个TS0；
				9：成帧模式1，发送端透传TS0、接收端也使用透传来的TS0（IDLE CODE一致时才可以使用此模式）；
				2：成帧模式2，发送端不发送TS0、接收端返回TS0（CRC除外，重新计算）；
				10：成帧模式3，发送端透传TS0、但接收端丢弃CRC使用重新计算的CRC；其它：保留。
			"
		::= { rcftRemoteDeviceE1Entry 20 }

        rcftRemoteE1PortIdleCode	OBJECT-TYPE
			SYNTAX	INTEGER
			MAX-ACCESS	read-write
			STATUS		current
			DESCRIPTION
			"
		       未用时隙的码字
			"
		::= { rcftRemoteDeviceE1Entry 21 }

       rcftRemoteE1LoopStatus  OBJECT-TYPE
       	SYNTAX	INTEGER
       	{
       		  localDoubleLoopEnable(1),
       		  localDoubleLoopDisable(2),
       		  remoteDoubleLoopEnable(3),
       		  remoteDoubleLoopDisable(4)
       	}
       	MAX-ACCESS read-only
       	STATUS	current
       	DESCRIPTION
       	"
       	     E1的环回状态：1:本地环回，2：无本地环回，3：远端环回，4：无远端环回，
       	     5:无环回，
       	     6：本地内环使能，7：本地外环使能，8：本地双向环使能，
       	     9:远端内环使能，10：远端外环使能，11：远端双向环使能，
       	     12：本地内环禁止，13:本地外环禁止，14：本地双向环禁止，
       	     15：远端内环禁止，16：远端外环禁止，17：远端双向环禁止，
       	"
        ::= { rcftRemoteDeviceE1Entry 22 }


		rcftRemoteE1OrderTimeParameter OBJECT-TYPE
			SYNTAX	INTEGER
			MAX-ACCESS read-write
			STATUS	current
			DESCRIPTION
	  		 "
	  		    给远端模块E1口发送命令时所需要赋的时长参数。

	  		    1: 测试时长1分钟
	  		    2: 测试时长2分钟
	  		    3: 测试时长4分钟
	  		    4: 测试时长8分钟
	  		    5: 测试时长15分钟
	  		    6: 测试时长30分钟
	  		    7: 测试时长60分钟

	  		    18: 测试2帧
	  		    19: 测试5帧
	  		    20: 测试10帧
	  		    21: 测试20帧
	  		    22: 测试50帧
	  		    23: 测试100帧
	  		"
            ::= { rcftRemoteDeviceE1Entry 23 }

      	rcftRemoteE1OrderModeParameter OBJECT-TYPE
			SYNTAX	INTEGER
			MAX-ACCESS read-write
			STATUS	current
			DESCRIPTION
	  		 "
	  		    给远端模块E1口发送命令时所需要赋的模式参数。

	  		"
            ::= { rcftRemoteDeviceE1Entry 24 }

		rcftRemoteE1Order	OBJECT-TYPE
			SYNTAX	INTEGER
			MAX-ACCESS	read-write
			STATUS	current
			DESCRIPTION
			"
			    1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
				22: 端口BERT测试开始
				23: 端口BERT测试结束

			注意：rcftRemoteE1Order的枚举值要和rcftRemoteDeviceOrder始终保持完全一致。
			"
		   ::= { rcftRemoteDeviceE1Entry 25 }

		rcftRemoteE1PortType	OBJECT-TYPE
			SYNTAX	INTEGER
			MAX-ACCESS	read-only
			STATUS	current
			DESCRIPTION
			"
			    表示E1的类型。这个节点主要是针对约定四而增加，用来区分多种E1子块
			    下各个E1的具体类型。

			    1：既可以为成帧，又可为非成帧（对应约定四中的0x10-0x04子块）
				2：非成帧（对应约定四中的0x10-0x06子块）
			"
		   ::= { rcftRemoteDeviceE1Entry 26 }

	    rcftRemoteE1BertStatus		OBJECT-TYPE
	    	SYNTAX  INTEGER
	    	MAX-ACCESS	read-write
	    	STATUS	current
	    	DESCRIPTION
	    	"
	    	  BIT3			BERT_STATUS		0:正常工作；	1:正在bert
	    	  BIT2-1		BERT_RESULT     00:未测试    01:测试正常；	10:测试失败
	    	  BIT0			BERT_TYPE   	0:误码率方式；  1:误码时间方式
	    	"
	    	::= {rcftRemoteDeviceE1Entry 27}

	    rcftRemoteE1BertTime		OBJECT-TYPE
	    	SYNTAX	Unsigned32
	    	MAX-ACCESS	read-only
	    	STATUS	current
	    	DESCRIPTION
	    	"
	    	误码率方式:测试时间，时间随测试的进行而增长，单位 S.
	    	"
	    	::= {rcftRemoteDeviceE1Entry  28}

	    rcftRemoteE1BertErrCode		OBJECT-TYPE
	    	SYNTAX	Unsigned32
	    	MAX-ACCESS	read-only
	    	STATUS	current
	    	DESCRIPTION
	    	"
	    	 误码率方式:误码数，单位是bit
	    	"
	    	::= {rcftRemoteDeviceE1Entry 29}

	    rcftRemoteE1BertUnusedTime		OBJECT-TYPE
	    	SYNTAX	Unsigned32
	    	MAX-ACCESS	read-only
	    	STATUS	current
	    	DESCRIPTION
	    	"
	    	 误码率方式:测试不可用时间，超过255秒后维持255秒不变，单位是S.
	    	"
	    	::= {rcftRemoteDeviceE1Entry 30}

	    rcftRemoteE1BertPortSpeed		OBJECT-TYPE
	    	SYNTAX	Unsigned32
	    	MAX-ACCESS	read-only
	    	STATUS	current
	    	DESCRIPTION
	    	"
	    	 误码率方式:测试的端口速率，单位：kbps。
	    	"
	    	::= {rcftRemoteDeviceE1Entry 31}

	   rcftRemoteE1BertCodeType		OBJECT-TYPE
	   		SYNTAX	 	INTEGER
	   		MAX-ACCESS	read-write
	   		STATUS	current
	   		DESCRIPTION
	   		"
	   		误码率方式:测试码型，最大值为127
	   		 0000001'b：215-1；
			 其它：保留。

	   		"
	   		::= {rcftRemoteDeviceE1Entry 32}

	   	rcftRemoteE1BertCodeNum		OBJECT-TYPE
	   		SYNTAX	INTEGER
	   		MAX-ACCESS	read-write
	   		STATUS	current
	   		DESCRIPTION
	   		"
	   		误码率方式:测试码数,最大值为127
	   		0000001'b：2的31次方个码；
			0000010'b：2的28次方个码；
			0000011'b：2的25次方个码；
			0000100'b：2的21次方个码；
			1111111'b：测试不停；
			其它：保留。

	   		"
	   		::= {rcftRemoteDeviceE1Entry 33}

       rcftRemoteE1LoopSwitchStatus  OBJECT-TYPE
       	SYNTAX	INTEGER
       	MAX-ACCESS read-only
       	STATUS	current
       	DESCRIPTION
       	"
       	     E1的环回状态（是拨码的状态而非实际状态，通常不用）：
       	     1:本地环回，2：无本地环回，3：远端环回，4：无远端环回，
       	     5:无环回，
       	     6：本地内环使能，7：本地外环使能，8：本地双向环使能，
       	     9:远端内环使能，10：远端外环使能，11：远端双向环使能，
       	     12：本地内环禁止，13:本地外环禁止，14：本地双向环禁止，
       	     15：远端内环禁止，16：远端外环禁止，17：远端双向环禁止，
       	"
        ::= { rcftRemoteDeviceE1Entry 34 }


        rcftRemoteE1AlarmRejest		OBJECT-TYPE
       	SYNTAX	INTEGER
       	MAX-ACCESS read-only
       	STATUS	current
       	DESCRIPTION
       	"
			E1告警屏蔽
			 1：屏蔽
			 2：不屏蔽
       	"
        ::= { rcftRemoteDeviceE1Entry 35 }

        rcftRemoteT1AlarmStatus	  OBJECT-TYPE
       	SYNTAX	INTEGER
       	MAX-ACCESS read-only
       	STATUS	current
       	DESCRIPTION
       	"
       	    本地T1告警
				Bit1 AIS	 0：告警， 1：正常
                Bit0 LOS	 0：告警； 1：正常。
       	"
        ::= { rcftRemoteDeviceE1Entry 36 }


	  rcftRemoteE1PortVCGNumber  OBJECT-TYPE
       	SYNTAX	INTEGER
       	MAX-ACCESS read-only
       	STATUS	current
       	DESCRIPTION
       	"
       	    接口属于哪个VCG成员。
				0：不是VCG成员。
			1~N：表示属与哪个VCG成员。
	   	"
        ::= { rcftRemoteDeviceE1Entry 37 }

       rcftRemoteE1ToLNumber OBJECT-TYPE
       	SYNTAX	INTEGER
       	MAX-ACCESS read-only
       	STATUS	current
       	DESCRIPTION
       	"
       	    对端E1编号。
	   	"
        ::= { rcftRemoteDeviceE1Entry 38 }

       rcftRemoteE1CVCnt OBJECT-TYPE
       	SYNTAX	INTEGER
       	MAX-ACCESS read-only
       	STATUS	current
       	DESCRIPTION
       	"
       	    E1编码违例统计。0~65535，累加值，非读清
	   	"
        ::= { rcftRemoteDeviceE1Entry 39 }

      rcftRemoteE1StatisticTable OBJECT-TYPE
	        SYNTAX SEQUENCE OF RcftRemoteE1StatisticEntry
	        MAX-ACCESS not-accessible
	        STATUS current
	        DESCRIPTION
	          "
	          远端设备E1端口的统计表.
	          "
            ::= {rcftRemoteDeviceE1Objects 2}

	    rcftRemoteE1StatisticEntry OBJECT-TYPE
	        SYNTAX RcftRemoteE1StatisticEntry
	        MAX-ACCESS not-accessible
	        STATUS current
	        DESCRIPTION
	          "
	            E1接口的性能统计表
	          "
	        AUGMENTS { rcftRemoteDeviceE1Entry }
	        ::= {rcftRemoteE1StatisticTable 1}

	    RcftRemoteE1StatisticEntry ::= SEQUENCE {

				rcftRemoteE1TxPackets         Counter32,
				rcftRemoteE1TxBytes           Counter32,
				rcftRemoteE1RxPackets         Counter32,
				rcftRemoteE1RxBytes           Counter32,
				rcftRemoteE1RxERRPackets      Counter32,
				rcftRemoteE1FluxTimer		  Counter32,
				rcftRemoteE1LANTxPackets	  Counter32,
				rcftRemoteE1LANRxPackets      Counter32,
				rcftRemoteE1LANRxLosPackets   Counter32

	         }

	 	rcftRemoteE1TxPackets OBJECT-TYPE
				SYNTAX Counter32
				MAX-ACCESS read-only
				STATUS current
				DESCRIPTION
					"
						远端设备E1端口发送以太网包数
					"
				::= { rcftRemoteE1StatisticEntry 1 }

		 rcftRemoteE1TxBytes OBJECT-TYPE
				SYNTAX Counter32
				MAX-ACCESS read-only
				STATUS current
				DESCRIPTION
					"
						远端设备E1端口发送以太网字节数
					"
				::= { rcftRemoteE1StatisticEntry 2 }

		 rcftRemoteE1RxPackets OBJECT-TYPE
				SYNTAX Counter32
				MAX-ACCESS read-only
				STATUS current
				DESCRIPTION
					"
						远端设备E1端口接收以太网包数
					"
				::= { rcftRemoteE1StatisticEntry 3 }

		 rcftRemoteE1RxBytes OBJECT-TYPE
				SYNTAX Counter32
				MAX-ACCESS read-only
				STATUS current
				DESCRIPTION
					"
						远端设备E1端口接收以太网字节数
					"
				::= { rcftRemoteE1StatisticEntry 4 }

	    rcftRemoteE1RxERRPackets OBJECT-TYPE
				SYNTAX Counter32
				MAX-ACCESS read-only
				STATUS current
				DESCRIPTION
					"
						远端设备E1端口接收错误以太网包数
					"
				::= { rcftRemoteE1StatisticEntry 5 }

		rcftRemoteE1FluxTimer	OBJECT-TYPE
				SYNTAX		Counter32
				MAX-ACCESS	read-only
				STATUS 		current
				DESCRIPTION
					"
						远端设备E1端口流量统计的时间
					"
				::= { rcftRemoteE1StatisticEntry 6 }

		rcftRemoteE1LANTxPackets	  OBJECT-TYPE
				SYNTAX Counter32
				MAX-ACCESS read-only
				STATUS current
				DESCRIPTION
					"
						远端设备E1端口LAN侧发送以太网包数
					"
				::= { rcftRemoteE1StatisticEntry 7 }

		rcftRemoteE1LANRxPackets      OBJECT-TYPE
				SYNTAX Counter32
				MAX-ACCESS read-only
				STATUS current
				DESCRIPTION
					"
						远端设备E1端口LAN侧接收以太网包数
					"
				::= { rcftRemoteE1StatisticEntry 8 }

		rcftRemoteE1LANRxLosPackets   OBJECT-TYPE
				SYNTAX Counter32
				MAX-ACCESS read-only
				STATUS current
				DESCRIPTION
					"
						远端设备E1端口LAN侧接收丢失以太网包数
					"
				::= { rcftRemoteE1StatisticEntry 9 }




	---以下是远端设备系统的TRAP定义--

		rcftRemoteDevExistTrap	NOTIFICATION-TYPE
			OBJECTS{
				 rcftRemoteDeviceExist
			}
			STATUS 	 current
			DESCRIPTION
			"
			      远端板卡在位状态变化告警，当远端板卡由在位到丢失时发送告警，
			      远端板卡由丢失到恢复在位时发送告警恢复.
 			"
		  	::={rcftRemoteDeviceSysTraps 1}

		rcftRemoteDevVoltTooHighTrap	NOTIFICATION-TYPE
			OBJECTS{
			         rcftRemoteSysVoltageStatus
			}
			STATUS	current
			DESCRIPTION
			"
				远端设备电压超出阀值时发送该告警
			"
            ::={rcftRemoteDeviceSysTraps 2}

		rcftRemoteDevVoltTooLowTrap	NOTIFICATION-TYPE
			OBJECTS{
			         rcftRemoteSysVoltageStatus
			}
			STATUS	current
			DESCRIPTION
			"
				远端设备电压超出阀值时发送该告警
			"
            ::={rcftRemoteDeviceSysTraps 3}

   		rcftRemoteDevTmptTrap NOTIFICATION-TYPE
	       OBJECTS {

	          rcftRemoteSysTemperature
	       }
	       STATUS  current
	       DESCRIPTION
	       "
	           远端模块所在机箱温度告警及恢复：当远端模块所在机箱温度高于门限值时发送告警，
	           当恢复到门限值范围内时发送告警恢复。
	       "
	       ::={ rcftRemoteDeviceSysTraps 4}

	      rcftRemoteDevPowerDownTrap NOTIFICATION-TYPE
	      	OBJECTS{
				rcftRemoteDevicePowerDown
	      	}
	       STATUS  current
	       DESCRIPTION
	       "
	           远端模块所接远端远端设备的掉电告警及恢复。
	       "
	       ::={ rcftRemoteDeviceSysTraps 5}

	      rcftRemoteDevPSChannelTrap NOTIFICATION-TYPE
	      	OBJECTS{
				rcftRemoteDeviceStatus
	      	}
	       STATUS  current
	       DESCRIPTION
	       "
	           主用通道切换到备用通道告警（没有恢复）。
	       "
	       ::={ rcftRemoteDeviceSysTraps 6}

 	      rcftRemoteDevSPChannelTrap NOTIFICATION-TYPE
	      	OBJECTS{
				rcftRemoteDeviceStatus
	      	}
	       STATUS  current
	       DESCRIPTION
	       "
	           备用通道切换到主用通道告警（没有恢复）。
	       "
	       ::={ rcftRemoteDeviceSysTraps 7}

	---以下是远端设备电口的TRAP定义--


	    rcftRemoteEthFeLinkTrap NOTIFICATION-TYPE
	        OBJECTS {

	           rcftRemoteEthFeLinkStatus
	        }
	        STATUS             current
	        DESCRIPTION
	        "
	           远端设备电口link状态变化告警及恢复.
	           当电口link状态由up变down时发送告警，由down变up时发送告警恢复.
	           The change of the link status of the eth port in the local module
	           will generate this trap.
	        "
	        ::= { rcftRemoteDeviceEthFeTraps 1 }

	---以下是远端设备光口的TRAP定义--

	     rcftRemoteEthFxPortRLKTrap  NOTIFICATION-TYPE
				OBJECTS{
				          rcftRemoteEthFxPortRLK
				}
	        STATUS             current
	        DESCRIPTION
	        "
	          本模块光口接收方向的link状态(1：linkup，2：linkdown).
	    	  The object indicating the status of the optical port
	    	  in the receiving direction.
	    	  When the value is 1 the optical port link up,otherwise link down.
	        "
	        ::= { rcftRemoteDeviceEthFxTraps 1 }

	    rcftRemoteEthFxPortTLKTrap  NOTIFICATION-TYPE
				OBJECTS{
				          rcftRemoteEthFxPortTLK
				}
	        STATUS             current
	        DESCRIPTION
	        "
	          远端设备光口发送方向的link状态(1：linkup，2：linkdown).
	    	  The object indicating the status of the optical port
	    	  in the receiving direction.
	    	  When the value is 1 the optical port link up,otherwise link down.
	        "
	        ::= { rcftRemoteDeviceEthFxTraps 2 }

	    rcftRemoteEthFxPortTxPowerTrap NOTIFICATION-TYPE
	       OBJECTS {
	          rcftRemoteEthFxPortTxPowerAbnormal
	       }
	       STATUS     current
	       DESCRIPTION
	       "
	       	本端发送光功率变化告警.
	       "
	       ::={ rcftRemoteDeviceEthFxTraps 3 }

	   rcftRemoteEthFxPortRxSensitiveTrap NOTIFICATION-TYPE
	       OBJECTS {

	          rcftRemoteEthFxPortRxSensitiveAbnormal
	       }
	       STATUS     current
	       DESCRIPTION
	       "
	         本端接收灵敏度变化告警.
	       "
	       ::={ rcftRemoteDeviceEthFxTraps 4 }


	   rcftRemoteEthFxPortLaserTrap NOTIFICATION-TYPE
	       OBJECTS {

	          rcftRemoteEthFxPortLaserAbnormal
	       }
	       STATUS     current
	       DESCRIPTION
	       "
	         本端激光管工作状态变化告警.
	       "
	       ::={ rcftRemoteDeviceEthFxTraps 5 }


	   rcftRemoteEthFxPortSDTrap NOTIFICATION-TYPE
	       OBJECTS {
	          rcftRemoteEthFxPortSD
	       }
	       STATUS     current
	       DESCRIPTION
	       "
	         本地光模块SD输出信号异常告警和恢复. 当rcftSlotOSD的状态值发生变化时
	         发送该trap. 是告警还是恢复由绑定的对象rcftSlotOSD的状态值决定：
	         1: 恢复，  2：告警
	       "
	       ::={ rcftRemoteDeviceEthFxTraps 6 }

	    rcftRemoteEthFxPortLinkTrap  NOTIFICATION-TYPE
				OBJECTS{
				          rcftRemoteEthFxPortLink
				}
	        STATUS             current
	        DESCRIPTION
	        "
	          远端设备光口的link状态(1：linkup，2：linkdown).
	    	  The object indicating the status of the optical port.
	    	  When the value is 1 the optical port link up,otherwise link down.
	        "
	        ::= { rcftRemoteDeviceEthFxTraps 7 }

	   rcftRemoteEthFxPortExitTrap   NOTIFICATION-TYPE
			OBJECTS{
				          rcftRemoteEthFxPortExist
				}
	        STATUS             current
	        DESCRIPTION
	        "
	          光模块在位trap。
	          1：在位，2：不在位
	        "
	        ::= { rcftRemoteDeviceEthFxTraps 8 }

	  rcftRemoteEthFxPortTempHighTrap   NOTIFICATION-TYPE
			OBJECTS{
				          rcftRemoteEthFxSFPDiagnoAlarmStatus
				}
	        STATUS             current
	        DESCRIPTION
	        "
	          sfp光模块数字诊断温度超高
	          1：恢复，2：告警
	        "
	        ::= { rcftRemoteDeviceEthFxTraps 9 }

	  rcftRemoteEthFxPortTempLowTrap     NOTIFICATION-TYPE
			OBJECTS{
				          rcftRemoteEthFxSFPDiagnoAlarmStatus
				}
	        STATUS             current
	        DESCRIPTION
	        "
	          sfp光模块数字诊断温度超低
	          1：恢复，2：告警
	        "
	        ::= { rcftRemoteDeviceEthFxTraps 10 }

	  rcftRemoteEthFxPortVoltageHighTrap   NOTIFICATION-TYPE
			OBJECTS{
				          rcftRemoteEthFxSFPDiagnoAlarmStatus
				}
	        STATUS             current
	        DESCRIPTION
	        "
	          sfp光模块数字诊断电压超高
	          1：恢复，2：告警
	        "
	        ::= { rcftRemoteDeviceEthFxTraps 11 }

	  rcftRemoteEthFxPortVoltageLowTrap   NOTIFICATION-TYPE
			OBJECTS{
				          rcftRemoteEthFxSFPDiagnoAlarmStatus
				}
	        STATUS             current
	        DESCRIPTION
	        "
	          sfp光模块数字诊断电压超低
	          1：恢复，2：告警
	        "
	        ::= { rcftRemoteDeviceEthFxTraps 12 }

	  rcftRemoteEthFxPortOffsetCurrHighTrap   NOTIFICATION-TYPE
			OBJECTS{
				          rcftRemoteEthFxSFPDiagnoAlarmStatus
				}
	        STATUS             current
	        DESCRIPTION
	        "
	          sfp光模块数字诊断偏置电流超高
	          1：恢复，2：告警
	        "
	        ::= { rcftRemoteDeviceEthFxTraps 13 }

	  rcftRemoteEthFxPortOffsetCurrLowTrap   NOTIFICATION-TYPE
			OBJECTS{
				          rcftRemoteEthFxSFPDiagnoAlarmStatus
				}
	        STATUS             current
	        DESCRIPTION
	        "
	          sfp光模块数字诊断偏置电流超低
	          1：恢复，2：告警
	        "
	        ::= { rcftRemoteDeviceEthFxTraps 14 }

	  rcftRemoteEthFxPortSendPowerHighTrap   NOTIFICATION-TYPE
			OBJECTS{
				          rcftRemoteEthFxSFPDiagnoAlarmStatus
				}
	        STATUS             current
	        DESCRIPTION
	        "
	          sfp光模块数字诊断发送功率超高
	          1：恢复，2：告警
	        "
	        ::= { rcftRemoteDeviceEthFxTraps 15 }

	  rcftRemoteEthFxPortSendPowerLowTrap  NOTIFICATION-TYPE
			OBJECTS{
				          rcftRemoteEthFxSFPDiagnoAlarmStatus
				}
	        STATUS             current
	        DESCRIPTION
	        "
	          sfp光模块数字诊断发送功率超低
	          1：恢复，2：告警
	        "
	        ::= { rcftRemoteDeviceEthFxTraps 16 }

	  rcftRemoteEthFxPortRecvPowerHighTrap  NOTIFICATION-TYPE
			OBJECTS{
				          rcftRemoteEthFxSFPDiagnoAlarmStatus
				}
	        STATUS             current
	        DESCRIPTION
	        "
	          sfp光模块数字诊断接收功率超高
	          1：恢复，2：告警
	        "
	        ::= { rcftRemoteDeviceEthFxTraps 17 }

	  rcftRemoteEthFxPortRecvPowerLowTrap  NOTIFICATION-TYPE
			OBJECTS{
				          rcftRemoteEthFxSFPDiagnoAlarmStatus
				}
	        STATUS             current
	        DESCRIPTION
	        "
	          sfp光模块数字诊断接收功率超低
	          1：恢复，2：告警
	        "
	        ::= { rcftRemoteDeviceEthFxTraps 18 }

	  rcftRemoteEthFxPortRemotePowerDownTrap   NOTIFICATION-TYPE
			OBJECTS{
				          rcftRemoteEthFxSFPDiagnoAlarmStatus
				}
	        STATUS             current
	        DESCRIPTION
	        "
	          远端掉电告警	1：恢复，2：告警
	        "
	        ::= { rcftRemoteDeviceEthFxTraps 19 }

	   rcftRemoteEthFxPortInputSignalLosTrap   NOTIFICATION-TYPE
			OBJECTS{
				          rcftRemoteEthFxPortSFPInfo
				}
	        STATUS             current
	        DESCRIPTION
	        "
	          SFP输入信息丢失	1：恢复，2：告警
	        "
	        ::= { rcftRemoteDeviceEthFxTraps 20 }
	   rcftRemoteEthFxPortTempHighWarnning   NOTIFICATION-TYPE
			OBJECTS{
				          rcftRemoteEthFxSFPDiagnoAlarmStatus
				}
	        STATUS             current
	        DESCRIPTION
	        "
	          sfp光模块数字诊断温度超高
	          1：恢复，2：告警
	        "
	        ::= { rcftRemoteDeviceEthFxTraps 21 }

	  rcftRemoteEthFxPortTempLowWarning     NOTIFICATION-TYPE
			OBJECTS{
				          rcftRemoteEthFxSFPDiagnoWarningStatus
				}
	        STATUS             current
	        DESCRIPTION
	        "
	          sfp光模块数字诊断温度超低
	          1：恢复，2：告警
	        "
	        ::= { rcftRemoteDeviceEthFxTraps 22 }

	  rcftRemoteEthFxPortVoltageHighWarning   NOTIFICATION-TYPE
			OBJECTS{
				          rcftRemoteEthFxSFPDiagnoWarningStatus
				}
	        STATUS             current
	        DESCRIPTION
	        "
	          sfp光模块数字诊断电压超高
	          1：恢复，2：告警
	        "
	        ::= { rcftRemoteDeviceEthFxTraps 23 }

	  rcftRemoteEthFxPortVoltageLowWarning   NOTIFICATION-TYPE
			OBJECTS{
				          rcftRemoteEthFxSFPDiagnoWarningStatus
				}
	        STATUS             current
	        DESCRIPTION
	        "
	          sfp光模块数字诊断电压超低
	          1：恢复，2：告警
	        "
	        ::= { rcftRemoteDeviceEthFxTraps 24 }

	  rcftRemoteEthFxPortOffsetCurrHighWarning   NOTIFICATION-TYPE
			OBJECTS{
				          rcftRemoteEthFxSFPDiagnoWarningStatus
				}
	        STATUS             current
	        DESCRIPTION
	        "
	          sfp光模块数字诊断偏置电流超高
	          1：恢复，2：告警
	        "
	        ::= { rcftRemoteDeviceEthFxTraps 25 }

	  rcftRemoteEthFxPortOffsetCurrLowWarning   NOTIFICATION-TYPE
			OBJECTS{
				          rcftRemoteEthFxSFPDiagnoWarningStatus
				}
	        STATUS             current
	        DESCRIPTION
	        "
	          sfp光模块数字诊断偏置电流超低
	          1：恢复，2：告警
	        "
	        ::= { rcftRemoteDeviceEthFxTraps 26 }

	  rcftRemoteEthFxPortSendPowerHighWarning   NOTIFICATION-TYPE
			OBJECTS{
				          rcftRemoteEthFxSFPDiagnoWarningStatus
				}
	        STATUS             current
	        DESCRIPTION
	        "
	          sfp光模块数字诊断发送功率超高
	          1：恢复，2：告警
	        "
	        ::= { rcftRemoteDeviceEthFxTraps 27 }

	  rcftRemoteEthFxPortSendPowerLowWarning  NOTIFICATION-TYPE
			OBJECTS{
				          rcftRemoteEthFxSFPDiagnoWarningStatus
				}
	        STATUS             current
	        DESCRIPTION
	        "
	          sfp光模块数字诊断发送功率超低
	          1：恢复，2：告警
	        "
	        ::= { rcftRemoteDeviceEthFxTraps 28 }

	  rcftRemoteEthFxPortRecvPowerHighWarning  NOTIFICATION-TYPE
			OBJECTS{
				          rcftRemoteEthFxSFPDiagnoWarningStatus
				}
	        STATUS             current
	        DESCRIPTION
	        "
	          sfp光模块数字诊断接收功率超高
	          1：恢复，2：告警
	        "
	        ::= { rcftRemoteDeviceEthFxTraps 29 }

	  rcftRemoteEthFxPortRecvPowerLowWarning  NOTIFICATION-TYPE
			OBJECTS{
				          rcftRemoteEthFxSFPDiagnoWarningStatus
				}
	        STATUS             current
	        DESCRIPTION
	        "
	          sfp光模块数字诊断接收功率超低
	          1：恢复，2：告警
	        "
	        ::= { rcftRemoteDeviceEthFxTraps 30 }

	  rcftRemoteDevE1LOSTRAP NOTIFICATION-TYPE
	       OBJECTS {
	          rcftRemoteE1AlarmStatus
	       }
	       STATUS  current
	       DESCRIPTION
	        "
	        远端设备E1信号消失告警
	        "
	       ::={ rcftRemoteDeviceE1Traps 1}

	  rcftRemoteDevE1LOFTRAP NOTIFICATION-TYPE
	       OBJECTS {
	          rcftRemoteE1AlarmStatus
	       }
	       STATUS  current
	       DESCRIPTION
	       "
	       远端设备E1线路LOF告警
	       "
	       ::={ rcftRemoteDeviceE1Traps 2}

	  rcftRemoteDevE1CRCTRAP NOTIFICATION-TYPE
	       OBJECTS {

	          rcftRemoteE1AlarmStatus
	       }
	       STATUS  current
	       DESCRIPTION
	       "
	       远端设备E1线路CRC告警
	       "
	       ::={ rcftRemoteDeviceE1Traps 3}


	   rcftRemoteDevE1AISTrap NOTIFICATION-TYPE
	        OBJECTS {
	           rcftRemoteE1AlarmStatus
	        }
	        STATUS  current
	        DESCRIPTION
	        "
	        远端设备E1线路AIS告警.
	        "
	        ::= { rcftRemoteDeviceE1Traps 4 }

	    rcftRemoteDevE1TransErrorCodeMore10E-3 NOTIFICATION-TYPE
	    	OBJECTS{
	    	      rcftRemoteE1TransErrorCode
	    	}
	    	STATUS	current
	    	DESCRIPTION
	    	"
	    	   远端设备光传输误码率大于10E-3告警
	    	"
            ::= { rcftRemoteDeviceE1Traps 5 }

	    rcftRemoteDevE1TransErrorCodeMore10E-6 NOTIFICATION-TYPE
	    	OBJECTS{
	    	      rcftRemoteE1TransErrorCode
	    	}
	    	STATUS	current
	    	DESCRIPTION
	    	"
	    	   远端设备光传输误码率大于10E-6告警
	    	"
            ::= { rcftRemoteDeviceE1Traps 6 }

	  	rcftRemoteDevToLocalDevE1LOSTRAP NOTIFICATION-TYPE
	       OBJECTS {
	          rcftRemoteToLocalE1AlarmStatus
	       }
	       STATUS  current
	       DESCRIPTION
	        "
	        远端设备收到的其对端设备E1信号消失告警
	        "
	       ::={ rcftRemoteDeviceE1Traps 7}

	  	rcftRemoteDevToLocalDevE1LOFTRAP NOTIFICATION-TYPE
	       OBJECTS {
	          rcftRemoteToLocalE1AlarmStatus
	       }
	       STATUS  current
	       DESCRIPTION
	       "
	       远端设备收到的其对端设备E1线路LOF告警
	       "
	       ::={ rcftRemoteDeviceE1Traps 8}

	  	rcftRemoteDevToLocalDevE1CRCTRAP NOTIFICATION-TYPE
	       OBJECTS {

	          rcftRemoteToLocalE1AlarmStatus
	       }
	       STATUS  current
	       DESCRIPTION
	       "
	       远端设备收到的其对端设备E1线路CRC告警
	       "
	       ::={ rcftRemoteDeviceE1Traps 9}


	  	rcftRemoteDevToLocalDevE1AISTrap NOTIFICATION-TYPE
	        OBJECTS {
	           rcftRemoteToLocalE1AlarmStatus
	        }
	        STATUS  current
	        DESCRIPTION
	        "
	        远端设备收到的其对端设备E1线路AIS告警.
	        "
	        ::= { rcftRemoteDeviceE1Traps 10 }

	  	rcftRemoteDevE1CVTrap NOTIFICATION-TYPE
	        OBJECTS {
	           rcftRemoteE1AlarmStatus
	        }
	        STATUS  current
	        DESCRIPTION
	        "
	         远端设备E1线路CV告警.
	        "
	        ::= { rcftRemoteDeviceE1Traps 11 }

	  	rcftRemoteDevE1LOMFTrap NOTIFICATION-TYPE
	        OBJECTS {
	           rcftRemoteE1AlarmStatus
	        }
	        STATUS  current
	        DESCRIPTION
	        "
	         远端设备E1线路LOMF告警.
	        "
	        ::= { rcftRemoteDeviceE1Traps 12 }
	   rcftRemoteDevT1LOSTrap    NOTIFICATION-TYPE
	        OBJECTS {
	           rcftRemoteT1AlarmStatus
	        }
	        STATUS  current
	        DESCRIPTION
	        "
	         远端设备T1线路LOS告警.
	        "
	        ::= { rcftRemoteDeviceE1Traps 13 }

	   rcftRemoteDevT1AISTrap    NOTIFICATION-TYPE
	        OBJECTS {
	           rcftRemoteT1AlarmStatus
	        }
	        STATUS  current
	        DESCRIPTION
	        "
	         远端设备T1线路AIS告警.
	        "
	        ::= { rcftRemoteDeviceE1Traps 14 }

	   rcftRemoteDevE1TSDTrap    NOTIFICATION-TYPE
	        OBJECTS {
	           rcftRemoteE1AlarmStatus
	        }
	        STATUS  current
	        DESCRIPTION
	        "
	         远端设备E1线路TSD告警.
	        "
	        ::= { rcftRemoteDeviceE1Traps 15 }

	    rcftRemoteE1PortToLTSDTrap NOTIFICATION-TYPE
	        OBJECTS {
	           rcftRemoteE1AlarmStatus
	        }
	        STATUS  current
	        DESCRIPTION
	        "
	         远端设备的对端E1线路TSD告警.
	        "
	        ::= { rcftRemoteDeviceE1Traps 16 }


	   	rcftRemoteDevE1RDITrap NOTIFICATION-TYPE
	        OBJECTS {
	           rcftRemoteE1AlarmStatus
	        }
	        STATUS  current
	        DESCRIPTION
	        "
	         远端设备E1线路RDI告警，当其对端出现LOS、AIS、LOF中的任何一个时，引发本地RDI告警.
	        "
	        ::= { rcftRemoteDeviceE1Traps 17 }

	   	rcftRemoteE1PortToLLOMFTrap NOTIFICATION-TYPE
	        OBJECTS {
	           rcftRemoteE1AlarmStatus
	        }
	        STATUS  current
	        DESCRIPTION
	        "
	         远端设备的对端E1线路 LOMF 告警.
	        "
	        ::= { rcftRemoteDeviceE1Traps 18 }





   --------------------------G.端口的对象---------------------------------

    rcftRemoteSHDSLPortTable OBJECT-TYPE
       SYNTAX  SEQUENCE OF RcftRemoteSHDSLPortEntry
       MAX-ACCESS  not-accessible
       STATUS  current
       DESCRIPTION
       "
         The SDHSL PORT table.
       "
       ::= { rcftRemoteSHDSLPortObjects 1 }

    rcftRemoteSHDSLPortEntry OBJECT-TYPE
       SYNTAX  RcftRemoteSHDSLPortEntry
       MAX-ACCESS  not-accessible
       STATUS  current
       DESCRIPTION
       "
          An entry in the SHDSL PORT table.

       "
       INDEX   { rcftChassisIndex, rcftSlotIndex,rcftRemoteDeviceIndex,rcftRemoteSHDSLPortIndex }
       ::= { rcftRemoteSHDSLPortTable 1 }


    RcftRemoteSHDSLPortEntry ::=
       SEQUENCE {
       rcftRemoteSHDSLPortIndex		 		Integer32,
       rcftRemoteSHDSLPortAlarmStatus		INTEGER,
       rcftRemoteSHDSLPortStatus			INTEGER,
       rcftRemoteSHDSLPortCapableSpeed		INTEGER,
       rcftRemoteSHDSLPortWorkSpeed			INTEGER,
       rcftRemoteSHDSLPortProbeMaxSpeed		INTEGER,
       rcftRemoteSHDSLPortProbeMinSpeed		INTEGER,
       rcftRemoteSDHSLPortSNR				INTEGER,
       rcftRemoteSHDSLPortConfigSNR			INTEGER,
       rcftRemoteSHDSLPortSNRThreshold   	INTEGER,
       rcftRemoteSHDSLPortAttenuation 		INTEGER,
       rcftRemoteSHDSLPortAttenuationThreshold		INTEGER,
       rcftRemoteSHDSLPortPBO   			INTEGER,
       rcftRemoteSHDSLPortLOSThreshold		INTEGER,
       rcftRemoteSHDSLPortLOSWThreshold		INTEGER,
       rcftRemoteSHDSLPortLOLKThreshold		INTEGER,
       rcftRemoteSHDSLPortESThreshold		INTEGER,
       rcftRemoteSHDSLPortLoopStatus		INTEGER,
       rcftRemoteSHDSLPortAttenuationInitThreshhold	INTEGER,
	   rcftRemoteSHDSLPortOrderTimeParameter		INTEGER,
	   rcftRemoteSHDSLPortOrderModeParameter		INTEGER,
	   rcftRemoteSHDSLPortOrder						INTEGER,
       rcftRemoteSHDSLPortPBOAmount   			INTEGER,
       rcftRemoteSHDSLBertStatus				INTEGER,
	   rcftRemoteSHDSLBertTime			    	Unsigned32,
	   rcftRemoteSHDSLBertErrCode				Unsigned32,
	   rcftRemoteSHDSLBertUnusedTime			Unsigned32,
	   rcftRemoteSHDSLBertPortSpeed				Unsigned32,
	   rcftRemoteSHDSLBertCodeType			INTEGER,
	   rcftRemoteSHDSLBertCodeNum			INTEGER,
	   rcftRemoteSHDSLLoopStatus		INTEGER
		}

    rcftRemoteSHDSLPortIndex OBJECT-TYPE
    	SYNTAX	   Integer32
    	MAX-ACCESS read-only
    	STATUS		current
    	DESCRIPTION
    	"
    		G.口的索引
    	"
        ::= { rcftRemoteSHDSLPortEntry 1 }

     rcftRemoteSHDSLPortAlarmStatus   OBJECT-TYPE
     	SYNTAX	INTEGER
     	MAX-ACCESS	read-only
     	STATUS		current
     	DESCRIPTION
     	"
     		G.口的告警状态。

     		BIT5: SHDSL-LOS	SHDSL端口LOS时该位清0，否则置1。
            BIT4: SHDSL-LOSW	SHDSL端口LOSW时该位清0，否则置1。
            BIT3: SHDSL-Link	SHDSL端口为link up状态该位置1，否则清0。
            BIT2: 保留	固定为0'b。
            BIT1: FEC	SHDSL端口有FEC错误时该位清0，否则置1。
            BIT0: CRC	SHDSL端口有CRC错误时该位清0，否则置1。
     	"
 	    ::= { rcftRemoteSHDSLPortEntry 2 }


      rcftRemoteSHDSLPortStatus   OBJECT-TYPE
     	SYNTAX	INTEGER
     	MAX-ACCESS	read-write
     	STATUS		current
     	DESCRIPTION
     	"
     		G.口的状态。
			BIT23-22 IN_LBK-Test 00：没有进行过环回测试； 01：保留；10：内环测试成功；11：内环测试失败。
			BIT21-20 EX_LBK-Test 00：没有进行过环回测试； 01：保留；10：外环测试成功；11：外环测试失败。
            BIT19-16 保留
     		BIT15-14 Port_En 	00：端口开；01：端口关；10：因故障转移关（无）；11：保留。
     		BIT13    LOC_FP_EN	1：使能本地xx端口故障向SHDSL口转移；  0：禁止。
			BIT12    REM_FP_EN	1：使能远端xx端口故障向SHDSL口转移；  0：禁止。
			BIT11	 BOOT状态	0：BOOT失败；1：BOOT成功。
			BIT10-9 保留
			BIT8：	SHDSL-synClock:   0:同步时钟， 1：准同步时钟
			BIT7-6	编码方式	00'b：TC-4PAM； 01'b：TC-16PAM；10'b：TC-32PAM。11'b：保留。
			BIT5-4	SHDSL-Annex	SHDSL端口采用AnnexA时：01b；为AnnexB时：10b；为AnnexF时：11b。
			BIT3	SHDSL-PSD	SHDSL端口采用对称PSD时该位置1，非对称PSD时清0。
			BIT2	SHDSL-Port-En	SHDSL端口为打开状态该位置1，为关闭状态则清0。
			BIT1	SHDSL-LineProbe	SHDSL端口为线路探测使能方式该位置1；否则清0。网管不需要处理！
			BIT0	STU-C	SHDSL端口工作于STU-C模式时该位置1，否则清0。
     	"
 	    ::= { rcftRemoteSHDSLPortEntry 3 }

	  rcftRemoteSHDSLPortCapableSpeed	OBJECT-TYPE
	  	SYNTAX	INTEGER
     	MAX-ACCESS	read-only
     	STATUS		current
     	DESCRIPTION
     	"
     		G.口最大可用速率,单位为64Kbps。
	  	"
	    ::= { rcftRemoteSHDSLPortEntry 4 }


	  rcftRemoteSHDSLPortWorkSpeed OBJECT-TYPE
     	SYNTAX	INTEGER
     	MAX-ACCESS	read-only
     	STATUS		current
     	DESCRIPTION
     	"
     		G.口的工作速率,单位为64Kbps。
     	"
 	    ::= { rcftRemoteSHDSLPortEntry 5 }

	  rcftRemoteSHDSLPortProbeMaxSpeed OBJECT-TYPE
     	SYNTAX	INTEGER
     	MAX-ACCESS	read-write
     	STATUS		current
     	DESCRIPTION
     	"
     		G.口处于线路探测方式时配置的允许最高速率,单位为64Kbps。
     	"
 	    ::= { rcftRemoteSHDSLPortEntry 6 }

	  rcftRemoteSHDSLPortProbeMinSpeed OBJECT-TYPE
     	SYNTAX	INTEGER
     	MAX-ACCESS	read-write
     	STATUS		current
     	DESCRIPTION
     	"
     		G.口处于线路探测方式时配置的允许最低速率,单位为64Kbps。
     	"
 	    ::= { rcftRemoteSHDSLPortEntry 7 }


 		rcftRemoteSDHSLPortSNR    OBJECT-TYPE
	     	SYNTAX	INTEGER
	     	MAX-ACCESS	read-only
	     	STATUS		current
	     	DESCRIPTION
	     	"
	     		G.口正常工作时的SNR（信噪比）,单位为0.5dB。是有符号数，有可能是负数。
	     	"
	 	    ::= { rcftRemoteSHDSLPortEntry 8 }

 		rcftRemoteSHDSLPortConfigSNR    OBJECT-TYPE
	     	SYNTAX	INTEGER
	     	MAX-ACCESS	read-write
	     	STATUS		current
	     	DESCRIPTION
	     	"
	     		G.口初始设置的SNR（信噪比）,单位为0.5dB。当linkup的瞬间G.口工作的SNR必须大于该
	     		初始值，之后rcftSDHSLPortSNR可以小于该初始值。是有符号数，有可能是负数。
	     	"
	 	    ::= { rcftRemoteSHDSLPortEntry 9 }

 	    rcftRemoteSHDSLPortSNRThreshold	OBJECT-TYPE
	     	SYNTAX	INTEGER
	     	MAX-ACCESS	read-write
	     	STATUS		current
	     	DESCRIPTION
	     	"
	     		G.口SNR（信噪比）的门限值,单位为0.5dB。
	     		当rcftSDHSLPortSNR小于该值时,AGENT发送告警。是有符号数，有可能是负数。
	     	"
	 	    ::= { rcftRemoteSHDSLPortEntry 10 }



 	    rcftRemoteSHDSLPortAttenuation	OBJECT-TYPE
	     	SYNTAX	INTEGER
	     	MAX-ACCESS	read-only
	     	STATUS		current
	     	DESCRIPTION
	     	"
	     		G.口的线路衰减值,单位为0.5dB。
	     	"
	 	    ::= { rcftRemoteSHDSLPortEntry 11 }


 	    rcftRemoteSHDSLPortAttenuationThreshold	OBJECT-TYPE
	     	SYNTAX	INTEGER
	     	MAX-ACCESS	read-write
	     	STATUS		current
	     	DESCRIPTION
	     	"
	     		G.口线路衰减值的门限值,单位为0.5dB。当RcftRemoteSHDSLPortAttenuation小于该门限值时
	     		AGENT发送告警。
	     	"
	 	    ::= { rcftRemoteSHDSLPortEntry 12 }

 	   	rcftRemoteSHDSLPortPBO  OBJECT-TYPE
	     	SYNTAX	INTEGER
	     	MAX-ACCESS	read-write
	     	STATUS		current
	     	DESCRIPTION
	     	"
	     		G.口线路功率回退结果
				BIT7	Valid	结果值有意义时为1，否则清0（0-6位无意义）。
				BIT6	PBO_AUTO	PBO自动设置时该位置1，PBO固定设置则清0。
				BIT5-4	保留	固定为00'b。
				BIT3-0	PBO值	PBO实际值，单位为dB。

	     	"
	 	    ::= { rcftRemoteSHDSLPortEntry 13 }

	 	 rcftRemoteSHDSLPortLOSThreshold OBJECT-TYPE
	     	SYNTAX	INTEGER
	     	MAX-ACCESS	read-write
	     	STATUS		current
	     	DESCRIPTION
	     	"
	     		当前15分钟LOS次数告警门限。取值范围是0-255。
	     	"
	 	    ::= { rcftRemoteSHDSLPortEntry 14 }


	 	 rcftRemoteSHDSLPortLOSWThreshold OBJECT-TYPE
	     	SYNTAX	INTEGER
	     	MAX-ACCESS	read-write
	     	STATUS		current
	     	DESCRIPTION
	     	"
	     		当前15分钟LOSW次数告警门限。取值范围是0-255。
	     	"
	 	    ::= { rcftRemoteSHDSLPortEntry 15 }


	 	 rcftRemoteSHDSLPortLOLKThreshold OBJECT-TYPE
	     	SYNTAX	INTEGER
	     	MAX-ACCESS	read-write
	     	STATUS		current
	     	DESCRIPTION
	     	"
	     		当前15分钟LOLK(linkdown)次数告警门限。取值范围是0-255。
	     	"
	 	    ::= { rcftRemoteSHDSLPortEntry 16 }

	 	 rcftRemoteSHDSLPortESThreshold OBJECT-TYPE
	     	SYNTAX	INTEGER
	     	MAX-ACCESS	read-write
	     	STATUS		current
	     	DESCRIPTION
	     	"
	     		当前15分钟误码秒告警门限。取值范围是0-255。
	     	"
	 	    ::= { rcftRemoteSHDSLPortEntry 17 }


	 	  rcftRemoteSHDSLPortLoopStatus	OBJECT-TYPE
	 	  	SYNTAX	INTEGER
	 	  	{
	 	  		insideLoop(1),
	 	  		outsideLoop(2),
	 	  		doubleloop(3),
	 	  		normal(100)
	 	  	}
	     	MAX-ACCESS	read-only
	     	STATUS		current
	     	DESCRIPTION
	     	"
	     		G.口的环回状态:1：内环，2：外环，3：内环外环同时存在,100：正常
	     	"
	 	    ::= { rcftRemoteSHDSLPortEntry 18 }


 	    rcftRemoteSHDSLPortAttenuationInitThreshhold	OBJECT-TYPE
	     	SYNTAX	INTEGER
	     	MAX-ACCESS	read-write
	     	STATUS		current
	     	DESCRIPTION
	     	"
	     		G.口的环路衰减初始门限值，单位为0.5dB。
	     	"
	 	    ::= { rcftRemoteSHDSLPortEntry 19 }

		rcftRemoteSHDSLPortOrderTimeParameter OBJECT-TYPE
			SYNTAX	INTEGER
			MAX-ACCESS read-write
			STATUS	current
			DESCRIPTION
	  		 "
	  		    给远端模块G.口发送命令时所需要赋的时长参数。

	  		    1: 测试时长1分钟
	  		    2: 测试时长2分钟
	  		    3: 测试时长4分钟
	  		    4: 测试时长8分钟
	  		    5: 测试时长15分钟
	  		    6: 测试时长30分钟
	  		    7: 测试时长60分钟

	  		    18: 测试2帧
	  		    19: 测试5帧
	  		    20: 测试10帧
	  		    21: 测试20帧
	  		    22: 测试50帧
	  		    23: 测试100帧
	  		"
            ::= { rcftRemoteSHDSLPortEntry 20 }

      	rcftRemoteSHDSLPortOrderModeParameter OBJECT-TYPE
			SYNTAX	INTEGER
			MAX-ACCESS read-write
			STATUS	current
			DESCRIPTION
	  		 "
	  		    给远端模块G.口发送命令时所需要赋的模式参数。

	  		"
            ::= { rcftRemoteSHDSLPortEntry 21 }

		rcftRemoteSHDSLPortOrder	OBJECT-TYPE
			SYNTAX	INTEGER
			MAX-ACCESS	read-write
			STATUS	current
			DESCRIPTION
			"
			    1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
				22: 端口BERT测试开始
				23: 端口BERT测试结束

			"
		   ::= { rcftRemoteSHDSLPortEntry 22 }

 	   	rcftRemoteSHDSLPortPBOAmount  OBJECT-TYPE
	     	SYNTAX	INTEGER
	     	MAX-ACCESS	read-write
	     	STATUS		current
	     	DESCRIPTION
	     	"
				PBO实际值，单位为dB。
	     	"
	 	    ::= { rcftRemoteSHDSLPortEntry 23 }

	    rcftRemoteSHDSLBertStatus		OBJECT-TYPE
	    	SYNTAX  INTEGER
	    	MAX-ACCESS	read-only
	    	STATUS	current
	    	DESCRIPTION
	    	"
	    	  BIT3			BERT_STATUS		0:正常工作；	1:正在bert
	    	  BIT2-1		BERT_RESULT     00:未测试      01:测试正常；	10:测试失败
	    	  BIT0			BERT_TYPE   	0:误码率方式；  1:误码时间方式
	    	"
	    	::= {rcftRemoteSHDSLPortEntry 24}

	    rcftRemoteSHDSLBertTime		OBJECT-TYPE
	    	SYNTAX	Unsigned32
	    	MAX-ACCESS	read-only
	    	STATUS	current
	    	DESCRIPTION
	    	"
	    	误码率方式:测试时间，时间随测试的进行而增长,单位 S.
	    	"
	    	::= {rcftRemoteSHDSLPortEntry  25}

	    rcftRemoteSHDSLBertErrCode		OBJECT-TYPE
	    	SYNTAX	Unsigned32
	    	MAX-ACCESS	read-only
	    	STATUS	current
	    	DESCRIPTION
	    	"
	    	 误码率方式:误码数，单位是bit
	    	"
	    	::= {rcftRemoteSHDSLPortEntry 26}

	    rcftRemoteSHDSLBertUnusedTime		OBJECT-TYPE
	    	SYNTAX	Unsigned32
	    	MAX-ACCESS	read-only
	    	STATUS	current
	    	DESCRIPTION
	    	"
	    	 误码率方式:测试不可用时间，超过255秒后维持255秒不变，单位是S.
	    	"
	    	::= {rcftRemoteSHDSLPortEntry 27}

	    rcftRemoteSHDSLBertPortSpeed		OBJECT-TYPE
	    	SYNTAX	Unsigned32
	    	MAX-ACCESS	read-only
	    	STATUS	current
	    	DESCRIPTION
	    	"
	    	 误码率方式:测试的端口速率，单位：kbps。
	    	"
	    	::= {rcftRemoteSHDSLPortEntry 28}

	    rcftRemoteSHDSLBertCodeType		OBJECT-TYPE
	   		SYNTAX INTEGER
	   		MAX-ACCESS	read-write
	   		STATUS	current
	   		DESCRIPTION
	   		"
	   		误码率方式:测试码型，最大值为127
	   		0000001'b：2-15-1；
			其它：保留。

	   		"
	   		::= {rcftRemoteSHDSLPortEntry 29}

	    rcftRemoteSHDSLBertCodeNum		OBJECT-TYPE
	   		SYNTAX INTEGER
	   		MAX-ACCESS	read-write
	   		STATUS	current
	   		DESCRIPTION
	   		"
	   		误码率方式:测试码数
	   		0000001'b：2的31次方个码；
			0000010'b：2的28次方个码；
			0000011'b：2的25次方个码；
			0000100'b：2的21次方个码；
			1111111'b：测试不停；
			其它：保留。

	   		"
	   		::= {rcftRemoteSHDSLPortEntry 30}

	   	rcftRemoteSHDSLLoopStatus  OBJECT-TYPE
       	SYNTAX	INTEGER
       	{
       		  localDoubleLoopEnable(1),
       		  localDoubleLoopDisable(2),
       		  remoteDoubleLoopEnable(3),
       		  remoteDoubleLoopDisable(4),
       		  normal(5),
       		  localInSideLoopEnale(6),
       		  localOutSideLoopEnable(7)

       	}
       	MAX-ACCESS read-only
       	STATUS	current
       	DESCRIPTION
       	"
       	     G.口的环回状态：1:本地环回，2：无本地环回，3：远端环回，4：无远端环回，
       	     5:无环回，
       	     6：本地内环使能，7：本地外环使能，8：本地双向环使能，
       	     9:远端内环使能，10：远端外环使能，11：远端双向环使能，
       	     12：本地内环禁止，13:本地外环禁止，14：本地双向环禁止，
       	     15：远端内环禁止，16：远端外环禁止，17：远端双向环禁止，
       	"
        ::= {rcftRemoteSHDSLPortEntry 31}

	 	 rcftRemoteSHDSLPortCurrentTable OBJECT-TYPE
	 	 	SYNTAX  SEQUENCE OF RcftRemoteSHDSLPortCurrentEntry
	 	 	MAX-ACCESS not-accessible
	 	 	STATUS current
	 	 	DESCRIPTION
	 	 	"
	 	 		G.口当前15分钟的性能统计表
	 	 	"
	 		::= { rcftRemoteSHDSLPortPerformance 1 }


	 	 rcftRemoteSHDSLPortCurrentEntry OBJECT-TYPE
 	      	SYNTAX  RcftRemoteSHDSLPortCurrentEntry
	 	 	MAX-ACCESS not-accessible
	 	 	STATUS current
	 	 	DESCRIPTION
	 	 	"
	 	 		G.口当前15分钟的性能统计表
	 	 	"
 	 	    INDEX{ rcftChassisIndex, rcftSlotIndex,rcftRemoteDeviceIndex,rcftRemoteSHDSLPortIndex }
	 		::= { rcftRemoteSHDSLPortCurrentTable 1 }


	 	 RcftRemoteSHDSLPortCurrentEntry ::=
	 	 	SEQUENCE{
	 	 	rcftRemoteSHDSLPortCurrentLOSTimes 		INTEGER,
	 	 	rcftRemoteSHDSLPortCurrentLOSWTimes 	INTEGER,
	 	 	rcftRemoteSHDSLPortCurrentLOLKTimes 	INTEGER,
	 	 	rcftRemoteSHDSLPortCurrentCVTimes 		INTEGER,
	 	 	rcftRemoteSHDSLPortCurrentES			INTEGER,
	 	 	rcftRemoteSHDSLPortCurrentSES			INTEGER,
	 	 	rcftRemoteSHDSLPortCurrentUAS			INTEGER,
	 	 	rcftRemoteSHDSLPortCurrentLOSWS      	INTEGER,
	 	 	rcftRemoteSHDSLPortCurrentCRCTimes      INTEGER
	 	 }

	 	rcftRemoteSHDSLPortCurrentLOSTimes OBJECT-TYPE
	     	SYNTAX	INTEGER
	     	MAX-ACCESS	read-only
	     	STATUS		current
	     	DESCRIPTION
	     	"
	     		G.口当前15分钟的LOS次数
	     	"
            ::= { rcftRemoteSHDSLPortCurrentEntry 1 }


	 	rcftRemoteSHDSLPortCurrentLOSWTimes OBJECT-TYPE
	     	SYNTAX	INTEGER
	     	MAX-ACCESS	read-only
	     	STATUS		current
	     	DESCRIPTION
	     	"
	     		G.口当前15分钟的LOSW次数
	     	"
            ::= { rcftRemoteSHDSLPortCurrentEntry 2 }


	 	rcftRemoteSHDSLPortCurrentLOLKTimes OBJECT-TYPE
	     	SYNTAX	INTEGER
	     	MAX-ACCESS	read-only
	     	STATUS		current
	     	DESCRIPTION
	     	"
	     		G.口当前15分钟的LINK DOWN的次数
	     	"
            ::= { rcftRemoteSHDSLPortCurrentEntry 3 }

	 	rcftRemoteSHDSLPortCurrentCVTimes OBJECT-TYPE
	     	SYNTAX	INTEGER
	     	MAX-ACCESS	read-only
	     	STATUS		current
	     	DESCRIPTION
	     	"
	     		G.口当前15分钟的CV的次数
	     	"
            ::= { rcftRemoteSHDSLPortCurrentEntry 4 }


	 	rcftRemoteSHDSLPortCurrentES OBJECT-TYPE
	     	SYNTAX	INTEGER
	     	MAX-ACCESS	read-only
	     	STATUS		current
	     	DESCRIPTION
	     	"
	     		G.口当前15分钟的误码秒数
	     	"
            ::= { rcftRemoteSHDSLPortCurrentEntry 5 }

	 	rcftRemoteSHDSLPortCurrentSES OBJECT-TYPE
	     	SYNTAX	INTEGER
	     	MAX-ACCESS	read-only
	     	STATUS		current
	     	DESCRIPTION
	     	"
	     		G.口当前15分钟的严重误码秒数
	     	"
            ::= { rcftRemoteSHDSLPortCurrentEntry 6 }

	 	rcftRemoteSHDSLPortCurrentUAS OBJECT-TYPE
	     	SYNTAX	INTEGER
	     	MAX-ACCESS	read-only
	     	STATUS		current
	     	DESCRIPTION
	     	"
	     		G.口当前15分钟的不可用秒数
	     	"
            ::= { rcftRemoteSHDSLPortCurrentEntry 7 }

	 	rcftRemoteSHDSLPortCurrentLOSWS OBJECT-TYPE
	     	SYNTAX	INTEGER
	     	MAX-ACCESS	read-only
	     	STATUS		current
	     	DESCRIPTION
	     	"
	     		G.口当前15分钟的LOSW秒数
	     	"
            ::= { rcftRemoteSHDSLPortCurrentEntry 8 }

	 	rcftRemoteSHDSLPortCurrentCRCTimes OBJECT-TYPE
	     	SYNTAX	INTEGER
	     	MAX-ACCESS	read-only
	     	STATUS		current
	     	DESCRIPTION
	     	"
	     		G.口当前15分钟的CRC的次数
	     	"
            ::= { rcftRemoteSHDSLPortCurrentEntry 9 }

	 	 rcftRemoteSHDSLPortIntervalTable OBJECT-TYPE
	 	 	SYNTAX  SEQUENCE OF RcftRemoteSHDSLPortIntervalEntry
	 	 	MAX-ACCESS not-accessible
	 	 	STATUS current
	 	 	DESCRIPTION
	 	 	"
	 	 		G.口最近若干个15分钟的性能统计表
	 	 	"
	 		::= { rcftRemoteSHDSLPortPerformance 2 }


	 	 rcftRemoteSHDSLPortIntervalEntry OBJECT-TYPE
 	      	SYNTAX  RcftRemoteSHDSLPortIntervalEntry
	 	 	MAX-ACCESS not-accessible
	 	 	STATUS current
	 	 	DESCRIPTION
	 	 	"
	 	 		G.口最近若干个15分钟的性能统计表
	 	 	"
 	 	    INDEX{ rcftChassisIndex, rcftSlotIndex ,rcftRemoteDeviceIndex
 	 	       ,rcftRemoteSHDSLPortIndex,rcftRemoteSHDSLPortIntervalNumber }
	 		::= { rcftRemoteSHDSLPortIntervalTable 1 }


	 	 RcftRemoteSHDSLPortIntervalEntry ::=
	 	 	SEQUENCE{
	 	 	rcftRemoteSHDSLPortIntervalNumber		INTEGER,
	 	 	rcftRemoteSHDSLPortIntervalLOSTimes 	INTEGER,
	 	 	rcftRemoteSHDSLPortIntervalLOSWTimes 	INTEGER,
	 	 	rcftRemoteSHDSLPortIntervalLOLKTimes 	INTEGER,
	 	 	rcftRemoteSHDSLPortIntervalCVTimes 	INTEGER,
	 	 	rcftRemoteSHDSLPortIntervalES			INTEGER,
	 	 	rcftRemoteSHDSLPortIntervalSES		INTEGER,
	 	 	rcftRemoteSHDSLPortIntervalUAS		INTEGER,
	 	 	rcftRemoteSHDSLPortIntervalLOSWS      INTEGER,
	 	 	rcftRemoteSHDSLPortIntervalCRCTimes 	INTEGER
	 	 }

	 	rcftRemoteSHDSLPortIntervalNumber  OBJECT-TYPE
	     	SYNTAX	INTEGER
	     	MAX-ACCESS	read-only
	     	STATUS		current
	     	DESCRIPTION
	     	"
	     		G.口最近的第几个15分钟
	     	"
            ::= { rcftRemoteSHDSLPortIntervalEntry 1 }


	 	rcftRemoteSHDSLPortIntervalLOSTimes OBJECT-TYPE
	     	SYNTAX	INTEGER
	     	MAX-ACCESS	read-only
	     	STATUS		current
	     	DESCRIPTION
	     	"
	     		G.口最近第几个15分钟的LOS次数
	     	"
            ::= { rcftRemoteSHDSLPortIntervalEntry 2 }


	 	rcftRemoteSHDSLPortIntervalLOSWTimes OBJECT-TYPE
	     	SYNTAX	INTEGER
	     	MAX-ACCESS	read-only
	     	STATUS		current
	     	DESCRIPTION
	     	"
	     		G.口最近第几个15分钟的LOSW次数
	     	"
            ::= { rcftRemoteSHDSLPortIntervalEntry 3 }


	 	rcftRemoteSHDSLPortIntervalLOLKTimes OBJECT-TYPE
	     	SYNTAX	INTEGER
	     	MAX-ACCESS	read-only
	     	STATUS		current
	     	DESCRIPTION
	     	"
	     		G.口最近第几个15分钟的LINK DOWN的次数
	     	"
            ::= { rcftRemoteSHDSLPortIntervalEntry 4 }

	 	rcftRemoteSHDSLPortIntervalCVTimes OBJECT-TYPE
	     	SYNTAX	INTEGER
	     	MAX-ACCESS	read-only
	     	STATUS		current
	     	DESCRIPTION
	     	"
	     		G.口最近第几个15分钟的CV的次数
	     	"
            ::= { rcftRemoteSHDSLPortIntervalEntry 5 }


	 	rcftRemoteSHDSLPortIntervalES OBJECT-TYPE
	     	SYNTAX	INTEGER
	     	MAX-ACCESS	read-only
	     	STATUS		current
	     	DESCRIPTION
	     	"
	     		G.口最近第几个15分钟的误码秒数
	     	"
            ::= { rcftRemoteSHDSLPortIntervalEntry 6 }

	 	rcftRemoteSHDSLPortIntervalSES OBJECT-TYPE
	     	SYNTAX	INTEGER
	     	MAX-ACCESS	read-only
	     	STATUS		current
	     	DESCRIPTION
	     	"
	     		G.口最近第几个15分钟的严重误码秒数
	     	"
            ::= { rcftRemoteSHDSLPortIntervalEntry 7 }

	 	rcftRemoteSHDSLPortIntervalUAS OBJECT-TYPE
	     	SYNTAX	INTEGER
	     	MAX-ACCESS	read-only
	     	STATUS		current
	     	DESCRIPTION
	     	"
	     		G.口最近第几个15分钟的不可用秒数
	     	"
            ::= { rcftRemoteSHDSLPortIntervalEntry 8 }

	 	rcftRemoteSHDSLPortIntervalLOSWS OBJECT-TYPE
	     	SYNTAX	INTEGER
	     	MAX-ACCESS	read-only
	     	STATUS		current
	     	DESCRIPTION
	     	"
	     		G.口最近第几个15分钟的LOSW秒数
	     	"
            ::= { rcftRemoteSHDSLPortIntervalEntry 9 }

	 	rcftRemoteSHDSLPortIntervalCRCTimes OBJECT-TYPE
	     	SYNTAX	INTEGER
	     	MAX-ACCESS	read-only
	     	STATUS		current
	     	DESCRIPTION
	     	"
	     		G.口最近第几个15分钟的CRC的次数
	     	"
            ::= { rcftRemoteSHDSLPortIntervalEntry 10 }

	 	 rcftRemoteSHDSLPortCurrentDayTable OBJECT-TYPE
	 	 	SYNTAX  SEQUENCE OF RcftRemoteSHDSLPortCurrentDayEntry
	 	 	MAX-ACCESS not-accessible
	 	 	STATUS current
	 	 	DESCRIPTION
	 	 	"
	 	 		G.口当前24小时的性能统计表
	 	 	"
	 		::= { rcftRemoteSHDSLPortPerformance 3 }


	 	 rcftRemoteSHDSLPortCurrentDayEntry OBJECT-TYPE
 	      	SYNTAX  RcftRemoteSHDSLPortCurrentDayEntry
	 	 	MAX-ACCESS not-accessible
	 	 	STATUS current
	 	 	DESCRIPTION
	 	 	"
	 	 		G.口当前24小时的性能统计表
	 	 	"
 	 	    INDEX{ rcftChassisIndex, rcftSlotIndex,rcftRemoteDeviceIndex,rcftRemoteSHDSLPortIndex }
	 		::= { rcftRemoteSHDSLPortCurrentDayTable 1 }


	 	 RcftRemoteSHDSLPortCurrentDayEntry ::=
	 	 	SEQUENCE{
	 	 	rcftRemoteSHDSLPortCurrentDayLOSTimes 	INTEGER,
	 	 	rcftRemoteSHDSLPortCurrentDayLOSWTimes 	INTEGER,
	 	 	rcftRemoteSHDSLPortCurrentDayLOLKTimes 	INTEGER,
	 	 	rcftRemoteSHDSLPortCurrentDayCVTimes 	INTEGER,
	 	 	rcftRemoteSHDSLPortCurrentDayES			INTEGER,
	 	 	rcftRemoteSHDSLPortCurrentDaySES		INTEGER,
	 	 	rcftRemoteSHDSLPortCurrentDayUAS		INTEGER,
	 	 	rcftRemoteSHDSLPortCurrentDayLOSWS      INTEGER,
	 	 	rcftRemoteSHDSLPortCurrentDayCRCTimes      INTEGER
	 	 }

	 	rcftRemoteSHDSLPortCurrentDayLOSTimes OBJECT-TYPE
	     	SYNTAX	INTEGER
	     	MAX-ACCESS	read-only
	     	STATUS		current
	     	DESCRIPTION
	     	"
	     		G.口当前24小时的LOS次数
	     	"
            ::= { rcftRemoteSHDSLPortCurrentDayEntry 1 }


	 	rcftRemoteSHDSLPortCurrentDayLOSWTimes OBJECT-TYPE
	     	SYNTAX	INTEGER
	     	MAX-ACCESS	read-only
	     	STATUS		current
	     	DESCRIPTION
	     	"
	     		G.口当前24小时的LOSW次数
	     	"
            ::= { rcftRemoteSHDSLPortCurrentDayEntry 2 }


	 	rcftRemoteSHDSLPortCurrentDayLOLKTimes OBJECT-TYPE
	     	SYNTAX	INTEGER
	     	MAX-ACCESS	read-only
	     	STATUS		current
	     	DESCRIPTION
	     	"
	     		G.口当前24小时的LINK DOWN的次数
	     	"
            ::= { rcftRemoteSHDSLPortCurrentDayEntry 3 }

	 	rcftRemoteSHDSLPortCurrentDayCVTimes OBJECT-TYPE
	     	SYNTAX	INTEGER
	     	MAX-ACCESS	read-only
	     	STATUS		current
	     	DESCRIPTION
	     	"
	     		G.口当前24小时的CV的次数
	     	"
            ::= { rcftRemoteSHDSLPortCurrentDayEntry 4 }


	 	rcftRemoteSHDSLPortCurrentDayES OBJECT-TYPE
	     	SYNTAX	INTEGER
	     	MAX-ACCESS	read-only
	     	STATUS		current
	     	DESCRIPTION
	     	"
	     		G.口当前24小时的误码秒数
	     	"
            ::= { rcftRemoteSHDSLPortCurrentDayEntry 5 }

	 	rcftRemoteSHDSLPortCurrentDaySES OBJECT-TYPE
	     	SYNTAX	INTEGER
	     	MAX-ACCESS	read-only
	     	STATUS		current
	     	DESCRIPTION
	     	"
	     		G.口当前24小时的严重误码秒数
	     	"
            ::= { rcftRemoteSHDSLPortCurrentDayEntry 6 }

	 	rcftRemoteSHDSLPortCurrentDayUAS OBJECT-TYPE
	     	SYNTAX	INTEGER
	     	MAX-ACCESS	read-only
	     	STATUS		current
	     	DESCRIPTION
	     	"
	     		G.口当前24小时的不可用秒数
	     	"
            ::= { rcftRemoteSHDSLPortCurrentDayEntry 7 }

	 	rcftRemoteSHDSLPortCurrentDayLOSWS OBJECT-TYPE
	     	SYNTAX	INTEGER
	     	MAX-ACCESS	read-only
	     	STATUS		current
	     	DESCRIPTION
	     	"
	     		G.口当前24小时的LOSW秒数
	     	"
            ::= { rcftRemoteSHDSLPortCurrentDayEntry 8 }

	 	rcftRemoteSHDSLPortCurrentDayCRCTimes OBJECT-TYPE
	     	SYNTAX	INTEGER
	     	MAX-ACCESS	read-only
	     	STATUS		current
	     	DESCRIPTION
	     	"
	     		G.口当前24小时的CRC的次数
	     	"
            ::= { rcftRemoteSHDSLPortCurrentDayEntry 9 }

	 	 rcftRemoteSHDSLPortIntervalDayTable OBJECT-TYPE
	 	 	SYNTAX  SEQUENCE OF RcftRemoteSHDSLPortIntervalDayEntry
	 	 	MAX-ACCESS not-accessible
	 	 	STATUS current
	 	 	DESCRIPTION
	 	 	"
	 	 		G.口最近若干个24小时的性能统计表
	 	 	"
	 		::= { rcftRemoteSHDSLPortPerformance 4 }


	 	 rcftRemoteSHDSLPortIntervalDayEntry OBJECT-TYPE
 	      	SYNTAX  RcftRemoteSHDSLPortIntervalDayEntry
	 	 	MAX-ACCESS not-accessible
	 	 	STATUS current
	 	 	DESCRIPTION
	 	 	"
	 	 		G.口最近若干个24小时的性能统计表
	 	 	"
 	 	    INDEX{ rcftChassisIndex, rcftSlotIndex,rcftRemoteDeviceIndex
 	 	    		,rcftRemoteSHDSLPortIndex,rcftRemoteSHDSLPortIntervalDayNumber }
	 		::= { rcftRemoteSHDSLPortIntervalDayTable 1 }


	 	 RcftRemoteSHDSLPortIntervalDayEntry ::=
	 	 	SEQUENCE{
	 	 	rcftRemoteSHDSLPortIntervalDayNumber		INTEGER,
	 	 	rcftRemoteSHDSLPortIntervalDayLOSTimes 	INTEGER,
	 	 	rcftRemoteSHDSLPortIntervalDayLOSWTimes 	INTEGER,
	 	 	rcftRemoteSHDSLPortIntervalDayLOLKTimes 	INTEGER,
	 	 	rcftRemoteSHDSLPortIntervalDayCVTimes 	INTEGER,
	 	 	rcftRemoteSHDSLPortIntervalDayES			INTEGER,
	 	 	rcftRemoteSHDSLPortIntervalDaySES		INTEGER,
	 	 	rcftRemoteSHDSLPortIntervalDayUAS		INTEGER,
	 	 	rcftRemoteSHDSLPortIntervalDayLOSWS      INTEGER,
	 	 	rcftRemoteSHDSLPortIntervalDayCRCTimes      INTEGER
	 	 }

	 	rcftRemoteSHDSLPortIntervalDayNumber  OBJECT-TYPE
	     	SYNTAX	INTEGER
	     	MAX-ACCESS	read-only
	     	STATUS		current
	     	DESCRIPTION
	     	"
	     		G.口最近的第几个24小时
	     	"
            ::= { rcftRemoteSHDSLPortIntervalDayEntry 1 }


	 	rcftRemoteSHDSLPortIntervalDayLOSTimes OBJECT-TYPE
	     	SYNTAX	INTEGER
	     	MAX-ACCESS	read-only
	     	STATUS		current
	     	DESCRIPTION
	     	"
	     		G.口最近第几个24小时的LOS次数
	     	"
            ::= { rcftRemoteSHDSLPortIntervalDayEntry 2 }


	 	rcftRemoteSHDSLPortIntervalDayLOSWTimes OBJECT-TYPE
	     	SYNTAX	INTEGER
	     	MAX-ACCESS	read-only
	     	STATUS		current
	     	DESCRIPTION
	     	"
	     		G.口最近第几个24小时的LOSW次数
	     	"
            ::= { rcftRemoteSHDSLPortIntervalDayEntry 3 }


	 	rcftRemoteSHDSLPortIntervalDayLOLKTimes OBJECT-TYPE
	     	SYNTAX	INTEGER
	     	MAX-ACCESS	read-only
	     	STATUS		current
	     	DESCRIPTION
	     	"
	     		G.口最近第几个24小时的LINK DOWN的次数
	     	"
            ::= { rcftRemoteSHDSLPortIntervalDayEntry 4 }

	 	rcftRemoteSHDSLPortIntervalDayCVTimes OBJECT-TYPE
	     	SYNTAX	INTEGER
	     	MAX-ACCESS	read-only
	     	STATUS		current
	     	DESCRIPTION
	     	"
	     		G.口最近第几个24小时的CV的次数
	     	"
            ::= { rcftRemoteSHDSLPortIntervalDayEntry 5 }


	 	rcftRemoteSHDSLPortIntervalDayES OBJECT-TYPE
	     	SYNTAX	INTEGER
	     	MAX-ACCESS	read-only
	     	STATUS		current
	     	DESCRIPTION
	     	"
	     		G.口最近第几个24小时的误码秒数
	     	"
            ::= { rcftRemoteSHDSLPortIntervalDayEntry 6 }

	 	rcftRemoteSHDSLPortIntervalDaySES OBJECT-TYPE
	     	SYNTAX	INTEGER
	     	MAX-ACCESS	read-only
	     	STATUS		current
	     	DESCRIPTION
	     	"
	     		G.口最近第几个24小时的严重误码秒数
	     	"
            ::= { rcftRemoteSHDSLPortIntervalDayEntry 7 }

	 	rcftRemoteSHDSLPortIntervalDayUAS OBJECT-TYPE
	     	SYNTAX	INTEGER
	     	MAX-ACCESS	read-only
	     	STATUS		current
	     	DESCRIPTION
	     	"
	     		G.口最近第几个24小时的不可用秒数
	     	"
            ::= { rcftRemoteSHDSLPortIntervalDayEntry 8 }

	 	rcftRemoteSHDSLPortIntervalDayLOSWS OBJECT-TYPE
	     	SYNTAX	INTEGER
	     	MAX-ACCESS	read-only
	     	STATUS		current
	     	DESCRIPTION
	     	"
	     		G.口最近第几个24小时的LOSW秒数
	     	"
            ::= { rcftRemoteSHDSLPortIntervalDayEntry 9 }

	 	rcftRemoteSHDSLPortIntervalDayCRCTimes OBJECT-TYPE
	     	SYNTAX	INTEGER
	     	MAX-ACCESS	read-only
	     	STATUS		current
	     	DESCRIPTION
	     	"
	     		G.口最近第几个24小时的CRC的次数
	     	"
            ::= { rcftRemoteSHDSLPortIntervalDayEntry 10 }

     ----------远端设备G.口的告警---------------------

      rcftRemoteSHDSLPortLOSTrap	NOTIFICATION-TYPE
      	OBJECTS{
			rcftRemoteSHDSLPortAlarmStatus
      	}
      	STATUS current
     	DESCRIPTION
     	"
     		远端设备上G.口的LOS告警
     	"
     	::= { rcftRemoteSHDSLPortTraps 1 }

      rcftRemoteSHDSLPortLOSWTrap	NOTIFICATION-TYPE
      	OBJECTS{
			rcftRemoteSHDSLPortAlarmStatus
      	}
      	STATUS current
     	DESCRIPTION
     	"
     		远端设备上G.口的LOSW告警
     	"
     	::= { rcftRemoteSHDSLPortTraps 2 }

      rcftRemoteSHDSLPortLINKTrap	NOTIFICATION-TYPE
      	OBJECTS{
			rcftRemoteSHDSLPortAlarmStatus
      	}
      	STATUS current
     	DESCRIPTION
     	"
     		远端设备上G.口的LINK告警
     	"
     	::= { rcftRemoteSHDSLPortTraps 3 }

      rcftRemoteSHDSLPortFECTrap	NOTIFICATION-TYPE
      	OBJECTS{
			rcftRemoteSHDSLPortAlarmStatus
			}
      	STATUS current
     	DESCRIPTION
     	"
     		远端设备上G.口的FEC告警
     	"
     	::= { rcftRemoteSHDSLPortTraps 4 }

      rcftRemoteSHDSLPortCRCTrap	NOTIFICATION-TYPE
      	OBJECTS{
			rcftRemoteSHDSLPortAlarmStatus
      	}
      	STATUS current
     	DESCRIPTION
     	"
     		远端设备上G.口的CRC告警
     	"
     	::= { rcftRemoteSHDSLPortTraps 5 }

      rcftRemoteSHDSLPortSNRThresholdTrap	NOTIFICATION-TYPE
      	OBJECTS{
			rcftRemoteSHDSLPortSNRThreshold
      	}
      	STATUS current
     	DESCRIPTION
     	"
     		远端设备上G.口的CRC告警
     	"
     	::= { rcftRemoteSHDSLPortTraps 6 }


      rcftRemoteSHDSLPortAttenuationThresholdTrap	NOTIFICATION-TYPE
      	OBJECTS{
			rcftRemoteSHDSLPortAttenuationThreshold
      	}
      	STATUS current
     	DESCRIPTION
     	"
     		远端设备上G.口的CRC告警
     	"
     	::= { rcftRemoteSHDSLPortTraps 7 }


      rcftRemoteSHDSLPortLOSThresholdTrap	NOTIFICATION-TYPE
      	OBJECTS{
			rcftRemoteSHDSLPortLOSThreshold
      	}
      	STATUS current
     	DESCRIPTION
     	"
     		远端设备上G.口的CRC告警
     	"
     	::= { rcftRemoteSHDSLPortTraps 8 }

       rcftRemoteSHDSLPortLOSWThresholdTrap NOTIFICATION-TYPE
      	OBJECTS{
			rcftRemoteSHDSLPortLOSWThreshold
      	}
      	STATUS current
     	DESCRIPTION
     	"
     		远端设备上G.口的CRC告警
     	"
     	::= { rcftRemoteSHDSLPortTraps 9 }


       rcftRemoteSHDSLPortLOLKThresholdTrap NOTIFICATION-TYPE
      	OBJECTS{
			rcftRemoteSHDSLPortLOLKThreshold
      	}
      	STATUS current
     	DESCRIPTION
     	"
     		远端设备上G.口的CRC告警
     	"
     	::= { rcftRemoteSHDSLPortTraps 10 }

       rcftRemoteSHDSLPortESThresholdTrap NOTIFICATION-TYPE
      	OBJECTS{
			rcftRemoteSHDSLPortESThreshold
      	}
      	STATUS current
     	DESCRIPTION
     	"
     		远端设备上G.口的CRC告警
     	"
     	::= { rcftRemoteSHDSLPortTraps 11 }

   --------------------------V35端口的对象---------------------------------

    rcftRemoteV35PortTable OBJECT-TYPE
       SYNTAX  SEQUENCE OF RcftRemoteV35PortEntry
       MAX-ACCESS  not-accessible
       STATUS  current
       DESCRIPTION
       "
         The Remote V35 PORT table.
       "
       ::= { rcftRemoteV35PortObjects 1 }

    rcftRemoteV35PortEntry OBJECT-TYPE
       SYNTAX  RcftRemoteV35PortEntry
       MAX-ACCESS  not-accessible
       STATUS  current
       DESCRIPTION
       "
          An entry in the Remote V35 PORT table.

       "
       INDEX   { rcftChassisIndex, rcftSlotIndex,
        			rcftRemoteDeviceIndex,rcftRemoteV35PortIndex }
       ::= { rcftRemoteV35PortTable 1 }


    RcftRemoteV35PortEntry ::=
       SEQUENCE {
       rcftRemoteV35PortIndex		Integer32,
       rcftRemoteV35PortAlarmStatus	INTEGER,
       rcftRemoteV35PortStatus		INTEGER,
       rcftRemoteV35PortSpeed		INTEGER,
	   rcftRemoteV35PortOrderTimeParameter		INTEGER,
	   rcftRemoteV35PortOrderModeParameter		INTEGER,
	   rcftRemoteV35PortOrder					INTEGER,
	   rcftRemoteV35BertStatus				INTEGER,
	   rcftRemoteV35BertTime			    Unsigned32,
	   rcftRemoteV35BertErrCode				Unsigned32,
	   rcftRemoteV35BertUnusedTime			Unsigned32,
	   rcftRemoteV35BertPortSpeed			Unsigned32,
	   rcftRemoteV35BertCodeType		INTEGER,
	   rcftRemoteV35BertCodeNum		INTEGER,
	   rcftRemoteV35LoopStatus		INTEGER

       }

    rcftRemoteV35PortIndex OBJECT-TYPE
    	SYNTAX	   Integer32
    	MAX-ACCESS read-only
    	STATUS		current
    	DESCRIPTION
    	"
    		RemoteV35口的索引
    	"
        ::= { rcftRemoteV35PortEntry 1 }

    rcftRemoteV35PortAlarmStatus	OBJECT-TYPE
    	SYNTAX	INTEGER
    	MAX-ACCESS read-only
    	STATUS		current
    	DESCRIPTION
    	"
			其它位	保留	固定000'b。
			BIT12	DSR_I		1：DSR信号UP；        0：DSR信号DOWN。
			BIT11	RAIS    站在本地设备上看对端V35口所占那一路E1的AIS告警 1：正常 	0：告警
			BIT10	RCV     站在本地设备上看对端V35口所占那一路E1的CV告警  1：正常 	0：告警
			BIT9	RLOF	站在本地设备上看对端V35口所占那一路E1的LOF告警 1：正常 	0：告警
			BIT8	AIS     V35口所占那一路E1的AIS告警 1：正常 	0：告警

			BIT7	CV          V35口所占那一路E1的CV告警  1：正常 	0：告警
			BIT6	LOF			V35口所占那一路E1的LOF告警 1：正常 	0：告警
			BIT5	PATT		1：误码测试正常       0：误码测试告警
			BIT4    CRC_ALARM   1：正常 			  0：告警

			BIT3	DCD_O		1：DCD信号UP；        0：DCD信号DOWN。
			BIT2	CTS_O		1：CTS信号UP；        0：CTS信号DOWN。
			BIT1	DTR_I		1：DTR信号UP；        0：DTR信号DOWN。
			BIT0	RTS_I		1：RTS信号UP；        0：RTS信号DOWN。
    	"
        ::= { rcftRemoteV35PortEntry 2 }

 	rcftRemoteV35PortStatus     OBJECT-TYPE
 		SYNTAX	INTEGER
    	MAX-ACCESS read-write
    	STATUS		current
    	DESCRIPTION
    	"
    		BIT25	 V35口带宽跟随：1：跟随； 0：不跟随
    		BIT24	 V35口占用时隙的成帧模式：1：成帧； 0：透明
			BIT23-22 IN_LBK-Test 00：没有进行过内环测试； 01：保留；10：内环测试成功；11：内环测试失败。
			BIT21-20 EX_LBK-Test 00：没有进行过环回测试； 01：保留；10：外环测试成功；11：外环测试失败。
			BIT19-18 CLOCK   	 00：从时钟  01：V35终端时钟，并且v35带宽不跟随
								 10：V35终端时钟，并且v35带宽跟随  11：主时钟
			BIT17-16 LOOP_STATE  00:不环回   01：本地环回  	 10：远端环回  11：保留

			BIT15-14 Port_En  	00：端口开(DCD=0、CTS=0)；01：端口关(DCD=1、CTS=1)；10：因故障转移关；        11：保留。
			BIT13    LOC_FP_EN	1：使能本地其它端口故障向V35口转移；  0：禁止。
			BIT12    REM_FP_EN	1：使能远端V35口故障向V35口转移；0：禁止。
			BIT11    Remote CRC_EN 站在本地上看远端V35口CRC功能  1：使能      0：禁止
			BIT10	 Local CRC_EN   1：使能      0：禁止
			BIT9-8   接口方式	00：M34M；01：HDB26M；其它：保留。

			BIT7    RCLK_AN		0：RXCLK时钟固定；    1：RXCLK时钟相位适应。
			BIT6    RCLK_INV	0：RXCLK时钟正相；1：RXCLK时钟反相。
			BIT5    TCLK_INV	0：TXCLK时钟正相；1：TXCLK时钟反相。
			BIT4    SA_DISABLE	1：不使用SA bit   0：使用SA bit
			BIT3	Rate_CFG   	1：时隙带宽主控   0：时隙带宽被控
			BIT2	BERT_EN		1：误码测试使能   0：误码测试禁止
			BIT1    DATA_V		0：输入数据中断； 1：输入数据正常。
			BIT0    CLK_V		0：输入时钟异常； 1：输入时钟正常。
    	"
        ::= { rcftRemoteV35PortEntry 3 }

    rcftRemoteV35PortSpeed	OBJECT-TYPE
 		SYNTAX	INTEGER
    	MAX-ACCESS read-write
    	STATUS		current
    	DESCRIPTION
		"
		   V35口的速率	单位为64Kbps。
		"
        ::= { rcftRemoteV35PortEntry 4 }

	rcftRemoteV35PortOrderTimeParameter OBJECT-TYPE
		SYNTAX	INTEGER
		MAX-ACCESS read-write
		STATUS	current
		DESCRIPTION
	  	"
	  	 给远端模块V35口发送命令时所需要赋的时长参数。

	  		    1: 测试时长1分钟
	  		    2: 测试时长2分钟
	  		    3: 测试时长4分钟
	  		    4: 测试时长8分钟
	  		    5: 测试时长15分钟
	  		    6: 测试时长30分钟
	  		    7: 测试时长60分钟

	  		    18: 测试2帧
	  		    19: 测试5帧
	  		    20: 测试10帧
	  		    21: 测试20帧
	  		    22: 测试50帧
	  		    23: 测试100帧
	  		"
        ::= { rcftRemoteV35PortEntry 5 }

      	rcftRemoteV35PortOrderModeParameter OBJECT-TYPE
			SYNTAX	INTEGER
			MAX-ACCESS read-write
			STATUS	current
			DESCRIPTION
	  		 "
	  		    给远端模块V35口发送命令时所需要赋的模式参数。

	  		"
            ::= { rcftRemoteV35PortEntry 6 }

		rcftRemoteV35PortOrder	OBJECT-TYPE
			SYNTAX	INTEGER
			MAX-ACCESS	read-write
			STATUS	current
			DESCRIPTION
			"
			    1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
				22: 端口BERT测试开始
				23: 端口BERT测试结束

			"
		   ::= { rcftRemoteV35PortEntry 7 }

		 rcftRemoteV35BertStatus		OBJECT-TYPE
	    	SYNTAX  INTEGER
	    	MAX-ACCESS	read-only
	    	STATUS	current
	    	DESCRIPTION
	    	"
	    	  BIT3			BERT_STATUS		0: 正常工作；	1: 正在bert
	    	  BIT2-1		BERT_RESULT     00:未测试      01:测试正常；	10:测试失败
	    	  BIT0			BERT_TYPE   	0: 误码率方式； 1: 误码时间方式
	    	"
	    	::= {rcftRemoteV35PortEntry 8}

	    rcftRemoteV35BertTime		OBJECT-TYPE
	    	SYNTAX	Unsigned32
	    	MAX-ACCESS	read-only
	    	STATUS	current
	    	DESCRIPTION
	    	"
	    	误码率方式:测试时间，时间随测试的进行而增长,单位 S.
	    	"
	    	::= {rcftRemoteV35PortEntry  9}

	    rcftRemoteV35BertErrCode		OBJECT-TYPE
	    	SYNTAX	Unsigned32
	    	MAX-ACCESS	read-only
	    	STATUS	current
	    	DESCRIPTION
	    	"
	    	 误码率方式:误码数，单位是bit
	    	"
	    	::= {rcftRemoteV35PortEntry 10}

	    rcftRemoteV35BertUnusedTime		OBJECT-TYPE
	    	SYNTAX	Unsigned32
	    	MAX-ACCESS	read-only
	    	STATUS	current
	    	DESCRIPTION
	    	"
	    	 误码率方式:测试不可用时间，超过255秒后维持255秒不变，单位是S.
	    	"
	    	::= {rcftRemoteV35PortEntry 11}

	    rcftRemoteV35BertPortSpeed		OBJECT-TYPE
	    	SYNTAX	Unsigned32
	    	MAX-ACCESS	read-only
	    	STATUS	current
	    	DESCRIPTION
	    	"
	    	 误码率方式:测试的端口速率，单位：kbps。
	    	"
	    	::= {rcftRemoteV35PortEntry 12}

	    rcftRemoteV35BertCodeType		OBJECT-TYPE
	   		SYNTAX	 	INTEGER
	   		MAX-ACCESS	read-write
	   		STATUS	current
	   		DESCRIPTION
	   		"
	   		误码率方式:测试码型，最大值为127
	   		0000001'b：215-1
	   		其它：保留。
	   		"
	   		::= {rcftRemoteV35PortEntry 13}

    	rcftRemoteV35BertCodeNum	OBJECT-TYPE
	   		SYNTAX	 	INTEGER
	   		MAX-ACCESS	read-write
	   		STATUS	current
	   		DESCRIPTION
	   		"
	   		误码率方式:测试码型，最大值为127
	   		0000001'b：2的31次方个码；
			0000010'b：2的28次方个码；
			0000011'b：2的25次方个码；
			0000100'b：2的21次方个码；
			1111111'b：测试不停；
			其它：保留。

	   		"
	   		::= {rcftRemoteV35PortEntry 14}

	   	rcftRemoteV35LoopStatus  OBJECT-TYPE
       	SYNTAX	INTEGER
       	{
       		  localDoubleLoopEnable(1),
       		  localDoubleLoopDisable(2),
       		  remoteDoubleLoopEnable(3),
       		  remoteDoubleLoopDisable(4),
       		  normal(5),
       		  localInSideLoopEnale(6),
       		  localOutSideLoopEnable(7)

       	}
       	MAX-ACCESS read-only
       	STATUS	current
       	DESCRIPTION
       	"
       	     V35的环回状态：1:本地环回，2：无本地环回，3：远端环回，4：无远端环回，
       	     5:无环回，
       	     6：本地内环使能，7：本地外环使能，8：本地双向环使能，
       	     9:远端内环使能，10：远端外环使能，11：远端双向环使能，
       	     12：本地内环禁止，13:本地外环禁止，14：本地双向环禁止，
       	     15：远端内环禁止，16：远端外环禁止，17：远端双向环禁止，
       	"
        ::= {rcftRemoteV35PortEntry 15}



    --------------------------V35端口的告警--------------------------

       rcftRemoteV35PortDCDTrap	NOTIFICATION-TYPE
      	OBJECTS{
			rcftRemoteV35PortAlarmStatus
      	}
      	STATUS current
     	DESCRIPTION
     	"
     		本端设备上V35端口的DCD告警
     	"
     	::= { rcftRemoteV35PortTraps 1 }


       rcftRemoteV35PortCTSTrap	NOTIFICATION-TYPE
      	OBJECTS{
			rcftRemoteV35PortAlarmStatus
      	}
      	STATUS current
     	DESCRIPTION
     	"
     		本端设备上V35端口的CTS告警
     	"
     	::= { rcftRemoteV35PortTraps 2 }


       rcftRemoteV35PortDTRTrap	NOTIFICATION-TYPE
      	OBJECTS{
			rcftRemoteV35PortAlarmStatus
      	}
      	STATUS current
     	DESCRIPTION
     	"
     		本端设备上V35端口的DTR告警
     	"
     	::= { rcftRemoteV35PortTraps 3 }


       rcftRemoteV35PortRTSTrap	NOTIFICATION-TYPE
      	OBJECTS{
			rcftRemoteV35PortAlarmStatus
      	}
      	STATUS current
     	DESCRIPTION
     	"
     		本端设备上V35端口的RTS告警
     	"
     	::= { rcftRemoteV35PortTraps 4 }


       rcftRemoteV35PortCRCTrap	NOTIFICATION-TYPE
      	OBJECTS{
			rcftRemoteV35PortAlarmStatus
      	}
      	STATUS current
     	DESCRIPTION
     	"
     		本端设备上V35端口占用的那一路E1的CRC告警
     	"
     	::= { rcftRemoteV35PortTraps 5 }


       rcftRemoteV35PortPATTTrap	NOTIFICATION-TYPE
      	OBJECTS{
			rcftRemoteV35PortAlarmStatus
      	}
      	STATUS current
     	DESCRIPTION
     	"
     		本端设备上V35端口占用的那一路E1的误码测试告警
     	"
     	::= { rcftRemoteV35PortTraps 6 }


       rcftRemoteV35PortLOFTrap	NOTIFICATION-TYPE
      	OBJECTS{
			rcftRemoteV35PortAlarmStatus
      	}
      	STATUS current
     	DESCRIPTION
     	"
     		本端设备上V35端口占用的那一路E1的LOF告警
     	"
     	::= { rcftRemoteV35PortTraps 7 }


       rcftRemoteV35PortCVTrap	NOTIFICATION-TYPE
      	OBJECTS{
			rcftRemoteV35PortAlarmStatus
      	}
      	STATUS current
     	DESCRIPTION
     	"
     		本端设备上V35端口占用的那一路E1的CV告警
     	"
     	::= { rcftRemoteV35PortTraps 8 }


       rcftRemoteV35PortAISTrap	NOTIFICATION-TYPE
      	OBJECTS{
			rcftRemoteV35PortAlarmStatus
      	}
      	STATUS current
     	DESCRIPTION
     	"
     		本端设备上V35端口占用的那一路E1的AIS告警
     	"
     	::= { rcftRemoteV35PortTraps 9 }

      rcftRemoteV35PortToLLOFTrap	NOTIFICATION-TYPE
      	OBJECTS{
			rcftRemoteV35PortAlarmStatus
      	}
      	STATUS current
     	DESCRIPTION
     	"
     		站在本地设备上看对端V35口所占那一路E1的LOF告警
     	"
     	::= { rcftRemoteV35PortTraps 10 }


       rcftRemoteV35PortToLCVTrap	NOTIFICATION-TYPE
      	OBJECTS{
			rcftRemoteV35PortAlarmStatus
      	}
      	STATUS current
     	DESCRIPTION
     	"
     		站在本地设备上看对端V35口所占那一路E1的CV告警
     	"
     	::= { rcftRemoteV35PortTraps 11 }


       rcftRemoteV35PortToLAISTrap	NOTIFICATION-TYPE
      	OBJECTS{
			rcftRemoteV35PortAlarmStatus
      	}
      	STATUS current
     	DESCRIPTION
     	"
     		站在本地设备上看对端V35口所占那一路E1的AIS告警
     	"
     	::= { rcftRemoteV35PortTraps 12 }


       rcftRemoteV35PortDSRTrap	NOTIFICATION-TYPE
      	OBJECTS{
			rcftRemoteV35PortAlarmStatus
      	}
      	STATUS current
     	DESCRIPTION
     	"
     		本端设备上V35端口的DSR告警
     	"
     	::= { rcftRemoteV35PortTraps 13 }

   --------------------------DS3E3端口的对象---------------------------------

   rcftRemoteDS3E3PortTable OBJECT-TYPE
       SYNTAX  SEQUENCE OF RcftRemoteDS3E3PortEntry
       MAX-ACCESS  not-accessible
       STATUS  current
       DESCRIPTION
       "
         The DS3E3 PORT table.
       "
       ::= { rcftRemoteDS3E3PortObjects 1 }

    rcftRemoteDS3E3PortEntry OBJECT-TYPE
       SYNTAX  RcftRemoteDS3E3PortEntry
       MAX-ACCESS  not-accessible
       STATUS  current
       DESCRIPTION
       "
          An entry in the DS3E3 PORT table.

       "
       INDEX   { rcftChassisIndex, rcftSlotIndex,
        			rcftRemoteDeviceIndex,rcftRemoteDS3E3PortIndex }
       ::= { rcftRemoteDS3E3PortTable 1 }


    RcftRemoteDS3E3PortEntry ::=
       SEQUENCE {
       rcftRemoteDS3E3PortIndex		 	Integer32,
       rcftRemoteDS3E3PortAlarmStatus	INTEGER,
       rcftRemoteDS3E3PortStatus		INTEGER,
       rcftRemoteDS3E3PortESCont		INTEGER,
       rcftRemoteDS3E3PortBertStatus	INTEGER,
       rcftRemoteDS3E3PortFaultFass		INTEGER,
       rcftRemoteDS3E3PortLoopStatus	INTEGER,
       rcftRemoteDS3E3PortOrder			INTEGER
       }

    rcftRemoteDS3E3PortIndex OBJECT-TYPE
    	SYNTAX	   Integer32
    	MAX-ACCESS read-only
    	STATUS		current
    	DESCRIPTION
    	"
    		DS3E3口的索引
    	"
        ::= { rcftRemoteDS3E3PortEntry 1 }


    rcftRemoteDS3E3PortAlarmStatus	OBJECT-TYPE
    	SYNTAX	INTEGER
    	MAX-ACCESS read-only
    	STATUS		current
    	DESCRIPTION
    	"
    		BIT8：  OOF    从本地设备上看对端设备接收信号帧失步告警 	1：正常    0：告警
            BIT7：  RAI    从本地设备上看对端设备RAI告警				1：正常    0：告警
    		BIT22： LOF    从本地设备上看对端设备电口LOF告警			1：正常	   0：告警
    		BIT21	CRC	   从本地设备上看对端设备电口CRC校验错告警		1：正常	   0：告警
			BIT20   RLCV   从本地设备上看对端设备电口编码冲突告警       1：正常    0：告警
			BIT19   RDMO   从本地设备上看对端设备电口发送信号无输出     1：正常    0：告警
			BIT18   RLOL   从本地设备上看对端设备电口接收信号失锁告警   1：正常    0：告警
			BIT17   RLOS   从本地设备上看对端设备电口接收信号丢失告警   1：正常    0：告警
			BIT16   RAIS   从本地设备上看对端设备电口接收信号AIS 告警   1：正常    0：告警

            BIT8：  OOF   接收信号帧失步告警 1：正常    0：告警
            BIT7：  RAI   RAI告警 			 1：正常    0：告警
            BIT6：  LOF   接收信号帧丢失告警 1：正常    0：告警
            BIT5	CRC	  CRC校验错告警		 1：正常	0：告警
			BIT4    LCV   编码冲突告警       1：正常    0：告警
			BIT3    DMO   发送信号无输出     1：正常    0：告警
			BIT2    LOL   接收信号失锁告警   1：正常    0：告警
			BIT1    LOS   接收信号丢失告警   1：正常    0：告警
			BIT0    AIS   接收信号AIS 告警   1：正常    0：告警
    	"
        ::= { rcftRemoteDS3E3PortEntry 2 }


	rcftRemoteDS3E3PortStatus	OBJECT-TYPE
		SYNTAX	INTEGER
		MAX-ACCESS read-write
		STATUS	current
		DESCRIPTION
		"
			 BIT10:  线路编码
			 		0:AMI
			 		1:B3ZS		--------------DS3
			 		1:HDB3      --------------E3
			 BIT9-8：帧结构:
			 		00:G.751	01:G.832   ------------E3
			 		00:M23		01:C-bit   ------------DS3

			 BIT7: 是否成帧				1: 成帧,	 0:非成帧
			 BIT6: DS3/E3传输距离		1：长距，	 0：短距
			 BIT5：保留
			 BIT4：保留
			 BIT3：保留

			 BIT2-1     端口的环回状态： 0：无环回，1：内环，2：外环，3：双向环
		     BIT0  		端口模式选择     0：E3    1：DS3
		"
		::= { rcftRemoteDS3E3PortEntry 3 }

	rcftRemoteDS3E3PortESCont	  OBJECT-TYPE
		SYNTAX  INTEGER
		MAX-ACCESS	read-only
		STATUS  current
		DESCRIPTION
		"
			误码秒个数
		"
        ::= { rcftRemoteDS3E3PortEntry 4 }

	rcftRemoteDS3E3PortBertStatus	OBJECT-TYPE
		SYNTAX  INTEGER
		MAX-ACCESS	read-only
		STATUS	current
		DESCRIPTION
		"
		1: 误码仪使能
		2: 误码仪禁止
		"
		::= { rcftRemoteDS3E3PortEntry 5 }

     rcftRemoteDS3E3PortFaultFass   OBJECT-TYPE
		SYNTAX  INTEGER
		MAX-ACCESS	read-write
		STATUS	current
		DESCRIPTION
		"
		1: 故障转移使能
		2: 故障转移禁止
		"
        ::= { rcftRemoteDS3E3PortEntry 6 }

 	  rcftRemoteDS3E3PortLoopStatus  OBJECT-TYPE
		 SYNTAX  INTEGER
		 MAX-ACCESS	read-only
		 STATUS	current
		 DESCRIPTION
		 "
		  	1: 本地环回，
			2：无本地环回，
			3：远端环回，
			4：无远端环回，
			5: 无环回，
			6：本地内环使能，
			7：本地外环使能，
			8：本地双向环使能，
			9：远端内环使能，
			10：远端外环使能，
			11：远端双向环使能，
			12：本地内环禁止，
			13: 本地外环禁止，
			14：本地双向环禁止，
			5： 远端内环禁止，
			16：远端外环禁止，
			17：远端双向环禁止，
		 "
         ::= { rcftRemoteDS3E3PortEntry 7 }


      rcftRemoteDS3E3PortOrder  OBJECT-TYPE
		  SYNTAX  INTEGER
		  MAX-ACCESS	read-write
		  STATUS	current
		  DESCRIPTION
		  "
		 		1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
 				22: 端口BERT测试开始
 				23: 端口BERT测试结束
		"
         ::= { rcftRemoteDS3E3PortEntry 8 }


    --------------------------DS3E3端口的流量统计------------------------


         rcftRemoteDS3E3StatisticTable OBJECT-TYPE
	        SYNTAX SEQUENCE OF RcftRemoteDS3E3StatisticEntry
	        MAX-ACCESS not-accessible
	        STATUS current
	        DESCRIPTION
	          "
	          局端设备DS3E3端口的统计表.
	          "
            ::= {rcftRemoteDS3E3PortPerformance 1}


	    rcftRemoteDS3E3StatisticEntry OBJECT-TYPE
	        SYNTAX RcftRemoteDS3E3StatisticEntry
	        MAX-ACCESS not-accessible
	        STATUS current
	        DESCRIPTION
	          "
	             以rcftRemoteDS3E3Index为索引
	          "
	        AUGMENTS { rcftRemoteDS3E3PortEntry }
	        ::= {rcftRemoteDS3E3StatisticTable 1}

	    RcftRemoteDS3E3StatisticEntry ::= SEQUENCE {
				rcftRemoteDS3E3TxPackets       Counter32,
				rcftRemoteDS3E3TxBytes           Counter32,
				rcftRemoteDS3E3TxFailurePackets   Counter32,
				rcftRemoteDS3E3RxPackets         Counter32,
				rcftRemoteDS3E3RxBytes           Counter32,
				rcftRemoteDS3E3RxErrorPackets    Counter32,
				rcftRemoteDS3E3FluxTimer	Counter32
	         }


    	  rcftRemoteDS3E3TxPackets OBJECT-TYPE
					SYNTAX Counter32
					MAX-ACCESS read-only
					STATUS current
					DESCRIPTION
						"
							DS3E3口发送以太网包数
						"
					::= { rcftRemoteDS3E3StatisticEntry 1 }

		rcftRemoteDS3E3TxBytes OBJECT-TYPE
					SYNTAX Counter32
					MAX-ACCESS read-only
					STATUS current
					DESCRIPTION
						"
							DS3E3口发送以太网字节数
						"
					::= { rcftRemoteDS3E3StatisticEntry 2 }


	    rcftRemoteDS3E3TxFailurePackets OBJECT-TYPE
					SYNTAX Counter32
					MAX-ACCESS read-only
					STATUS current
					DESCRIPTION
						"
							DS3E3电口发送以太网丢包数
						"
					::= { rcftRemoteDS3E3StatisticEntry 3 }

		 rcftRemoteDS3E3RxPackets OBJECT-TYPE
					SYNTAX Counter32
					MAX-ACCESS read-only
					STATUS current
					DESCRIPTION
						"
							DS3E3口接收以太网包数
						"
					::= { rcftRemoteDS3E3StatisticEntry 4 }

		 rcftRemoteDS3E3RxBytes OBJECT-TYPE
					SYNTAX Counter32
					MAX-ACCESS read-only
					STATUS current
					DESCRIPTION
						"
							DS3E3口接收以太网字节数
						"
					::= { rcftRemoteDS3E3StatisticEntry 5 }

	    rcftRemoteDS3E3RxErrorPackets OBJECT-TYPE
					SYNTAX Counter32
					MAX-ACCESS read-only
					STATUS current
					DESCRIPTION
						"
							DS3E3电口接收以太网丢包数
						"
					::= { rcftRemoteDS3E3StatisticEntry 6 }

        rcftRemoteDS3E3FluxTimer	OBJECT-TYPE
        			SYNTAX		Counter32
        			MAX-ACCESS 	read-only
        			STATUS		current
        			DESCRIPTION
        				"
        					流量统计的时间
        				"
                    ::= { rcftRemoteDS3E3StatisticEntry 7 }



    --------------------------DS3E3端口的告警------------------------

       rcftRemoteDS3E3PortAISTrap	NOTIFICATION-TYPE
      	OBJECTS{
			rcftRemoteDS3E3PortAlarmStatus
      	}
      	STATUS current
     	DESCRIPTION
     	"
     		本端设备上DS3E3端口的接收信号AIS告警
     	"
     	::= { rcftRemoteDS3E3PortTraps 1 }


       rcftRemoteDS3E3PortLOSTrap	NOTIFICATION-TYPE
      	OBJECTS{
			rcftRemoteDS3E3PortAlarmStatus
      	}
      	STATUS current
     	DESCRIPTION
     	"
     		本端设备上DS3E3端口的接收信号丢失告警
     	"
     	::= { rcftRemoteDS3E3PortTraps 2 }


       rcftRemoteDS3E3PortLOLTrap	NOTIFICATION-TYPE
      	OBJECTS{
			rcftRemoteDS3E3PortAlarmStatus
      	}
      	STATUS current
     	DESCRIPTION
     	"
     		本端设备上DS3E3端口的接收信号失锁告警
     	"
     	::= { rcftRemoteDS3E3PortTraps 3 }


       rcftRemoteDS3E3PortDMOTrap	NOTIFICATION-TYPE
      	OBJECTS{
			rcftRemoteDS3E3PortAlarmStatus
      	}
      	STATUS current
     	DESCRIPTION
     	"
     		本端设备上DS3E3端口的发送信号无输出告警
     	"
     	::= { rcftRemoteDS3E3PortTraps 4 }

       rcftRemoteDS3E3PortCVTrap	NOTIFICATION-TYPE
      	OBJECTS{
			rcftRemoteDS3E3PortAlarmStatus
      	}
      	STATUS current
     	DESCRIPTION
     	"
     		本端设备上DS3E3端口的编码冲突告警
     	"
     	::= { rcftRemoteDS3E3PortTraps 5 }

       rcftRemoteDS3E3PortCRCTrap	NOTIFICATION-TYPE
      	OBJECTS{
			rcftRemoteDS3E3PortAlarmStatus
      	}
      	STATUS current
     	DESCRIPTION
     	"
     		本端设备上DS3E3端口的CRC告警
     	"
     	::= { rcftRemoteDS3E3PortTraps 6 }

       rcftRemoteDS3E3PortToLAISTrap	NOTIFICATION-TYPE
      	OBJECTS{
			rcftRemoteDS3E3PortAlarmStatus
      	}
      	STATUS current
     	DESCRIPTION
     	"
     		从本地设备上看对端设备电口接收信号AIS 告警
       	"
     	::= { rcftRemoteDS3E3PortTraps 7 }


       rcftRemoteDS3E3PortToLLOSTrap	NOTIFICATION-TYPE
      	OBJECTS{
			rcftRemoteDS3E3PortAlarmStatus
      	}
      	STATUS current
     	DESCRIPTION
     	"
     		从本地设备上看对端设备电口接收信号LOS 告警
     	"
     	::= { rcftRemoteDS3E3PortTraps 8 }


       rcftRemoteDS3E3PortToLLOLTrap	NOTIFICATION-TYPE
      	OBJECTS{
			rcftRemoteDS3E3PortAlarmStatus
      	}
      	STATUS current
     	DESCRIPTION
     	"
     		从本地设备上看对端设备电口接收信号LOL 告警
     	"
     	::= { rcftRemoteDS3E3PortTraps 9 }


       rcftRemoteDS3E3PortToLDMOTrap	NOTIFICATION-TYPE
      	OBJECTS{
			rcftRemoteDS3E3PortAlarmStatus
      	}
      	STATUS current
     	DESCRIPTION
     	"
     		从本地设备上看对端设备电口发送信号无输出告警
     	"
     	::= { rcftRemoteDS3E3PortTraps 10 }


       rcftRemoteDS3E3PortToLCVTrap	NOTIFICATION-TYPE
      	OBJECTS{
			rcftRemoteDS3E3PortAlarmStatus
      	}
      	STATUS current
     	DESCRIPTION
     	"
     		从本地设备上看对端设备电口接收信号编码冲突告警
     	"
     	::= { rcftRemoteDS3E3PortTraps 11 }

       rcftRemoteDS3E3PortToLCRCTrap	NOTIFICATION-TYPE
      	OBJECTS{
			rcftRemoteDS3E3PortAlarmStatus
      	}
      	STATUS current
     	DESCRIPTION
     	"
     		从本地设备上看对端设备电口CRC告警
     	"
     	::= { rcftRemoteDS3E3PortTraps 12 }

     	rcftRemoteDS3E3PortLOFTrap	NOTIFICATION-TYPE
      	OBJECTS{
			rcftRemoteDS3E3PortAlarmStatus
      	}
      	STATUS current
     	DESCRIPTION
     	"
     		本端设备上DS3E3端口的LOF告警
     	"
     	::= { rcftRemoteDS3E3PortTraps 13 }

     	rcftRemoteDS3E3PortToLLOFTrap	NOTIFICATION-TYPE
      	OBJECTS{
			rcftRemoteDS3E3PortAlarmStatus
      	}
      	STATUS current
     	DESCRIPTION
     	"
     		从本地设备上看对端设备电口LOF告警
     	"
     	::= { rcftRemoteDS3E3PortTraps 14 }

        rcftRemoteDS3E3PortRAITrap	NOTIFICATION-TYPE
      	OBJECTS{
			rcftRemoteDS3E3PortAlarmStatus
      	}
      	STATUS current
     	DESCRIPTION
     	"
     		本端设备上DS3E3端口的RAI告警
     	"
     	::= { rcftRemoteDS3E3PortTraps 15 }

     	rcftRemoteDS3E3PortToLRAITrap	NOTIFICATION-TYPE
      	OBJECTS{
			rcftRemoteDS3E3PortAlarmStatus
      	}
      	STATUS current
     	DESCRIPTION
     	"
     		从本地设备上看对端设备电口RAI告警
     	"
     	::= { rcftRemoteDS3E3PortTraps 16 }

        rcftRemoteDS3E3PortOOFTrap	NOTIFICATION-TYPE
      	OBJECTS{
			rcftRemoteDS3E3PortAlarmStatus
      	}
      	STATUS current
     	DESCRIPTION
     	"
     		本端设备上DS3E3端口的OOF告警
     	"
     	::= { rcftRemoteDS3E3PortTraps 17 }

     	rcftRemoteDS3E3PortToLOOFTrap	NOTIFICATION-TYPE
      	OBJECTS{
			rcftRemoteDS3E3PortAlarmStatus
      	}
      	STATUS current
     	DESCRIPTION
     	"
     		从本地设备上看对端设备电口OOF告警
     	"
     	::= { rcftRemoteDS3E3PortTraps 18 }

   --------------------------pdh端口的对象---------------------------------

   rcftRemotePdhPortTable OBJECT-TYPE
       SYNTAX  SEQUENCE OF RcftRemotePdhPortEntry
       MAX-ACCESS  not-accessible
       STATUS  current
       DESCRIPTION
       "
         The Pdh PORT table.
       "
       ::= { rcftRemotePdhPortObjects 1 }

    rcftRemotePdhPortEntry OBJECT-TYPE
       SYNTAX  RcftRemotePdhPortEntry
       MAX-ACCESS  not-accessible
       STATUS  current
       DESCRIPTION
       "
          An entry in the Pdh PORT table.

       "
       INDEX   { rcftChassisIndex, rcftSlotIndex,
        			rcftRemoteDeviceIndex,rcftRemotePdhPortIndex }
       ::= { rcftRemotePdhPortTable 1 }


    RcftRemotePdhPortEntry ::=
       SEQUENCE {
       rcftRemotePdhPortIndex		Integer32,
       rcftRemotePdhPortModuleType	INTEGER,
       rcftRemotePdhPortAlarmStatus	INTEGER,
       rcftRemotePdhPortStatus		INTEGER,
       rcftRemotePdhPortECSCnt		INTEGER,
       rcftRemotePdhPortSECSCnt		INTEGER,
       rcftRemotePdhPortLoopStatus	INTEGER,
       rcftRemotePdhPortOrder		INTEGER,
       rcftRemotePdhPortBertStatus	INTEGER,
       rcftRemotePdhPortBertErrCode	Unsigned32
       }

    rcftRemotePdhPortIndex OBJECT-TYPE
    	SYNTAX	   Integer32
    	MAX-ACCESS read-only
    	STATUS		current
    	DESCRIPTION
    	"
    		Pdh口的索引
    	"
        ::= { rcftRemotePdhPortEntry 1 }

     rcftRemotePdhPortModuleType  OBJECT-TYPE
      	  SYNTAX INTEGER
      	  {
      	     optical-M(1),
      	     optical-S1(2),
      	     optical-S2(3),
      	     optical-S3(4),
      	     optical-SS13(5),
      	     optical-SS15(6),
      	     optical-SS23(7),
      	     optical-SS25(8),
      	     --optical-SS3(9),   kuanglili 20090519 根据公司规范取消ss3光头类型
      	     optical-SS34(9),
      	     optical-SS35(10),
      	     optical-S15(12),     --kuanglili 20090909 S15光模块的枚举为12
      	     optical-SFP(15),
      	     optical-SS24(23),
 	     	 optical-S1FC(50),
 	     	 optical-S1A(51),
 	     	 optical-S2A(52),
 	     	 optical-S3A(53),
      	     unknown-type(100)
      	  }
      	  MAX-ACCESS read-only
      	  STATUS current
      	  DESCRIPTION
      	  "
      	    远端设备pdh光口的光模块类型
      	  "
          ::= { rcftRemotePdhPortEntry 2 }

    rcftRemotePdhPortAlarmStatus	OBJECT-TYPE
    	SYNTAX	INTEGER
    	MAX-ACCESS read-only
    	STATUS		current
    	DESCRIPTION
    	"
			BIT20	从本地设备上查看到的对端设备掉电告警	 0：告警； 1：正常
			BIT19	从本地设备上查看到的对端设备光口的E-6	 0：告警； 1：正常
			BIT18	从本地设备上查看到的对端设备光口的E-3	 0：告警； 1：正常
			BIT17	从本地设备上查看到的对端设备光口的LOF	 0：告警； 1：正常
			BIT16	从本地设备上查看到的对端设备光口的LOS	 0：告警； 1：正常

			BIT3	E-6 pdh光口的E-6告警 0：告警； 1：正常
			BIT2	E-3	pdh光口的E-3告警 0：告警； 1：正常
			BIT1    LOF pdh光口LOF告警   0：告警   1：正常
			BIT0    LOS pdh光口LOS告警   0：告警   1：正常
    	"
        ::= { rcftRemotePdhPortEntry 3 }


	rcftRemotePdhPortStatus	OBJECT-TYPE
		SYNTAX	INTEGER
		MAX-ACCESS read-write
		STATUS	current
		DESCRIPTION
		"
			BIT10  光口故障转移           0：禁止   1：使能
			BIT9   光口所接的对端设备的掉电告警	 0：告警； 1：正常
			BIT8   光口ALS开关    	0:禁止       1: 使能
			BIT7-6 光口的环回状态 0：无环回，1：内环，2：外环 3：双向环
			BIT5   光口ALS    	0:禁止       1: 使能
			BIT4   从本地设备上查看到的对端设备光口的工作状态 0:不工作     1：工作
			BIT3   光口的工作状态 0:不工作     1：工作

			BIT2-1 光口因故障转移功能使能时的开关状态：
			       0：开
			       1：因电-光Faultpass功能使能时关闭
			       2：因光口ALS功能使能关闭
		    BIT0   光口的打开关闭：1:open, 0:close
		"
		::= { rcftRemotePdhPortEntry 4 }


     rcftRemotePdhPortECSCnt	OBJECT-TYPE
     	SYNTAX	INTEGER
     	MAX-ACCESS	read-only
     	STATUS	current
     	DESCRIPTION
     	"
     		pdh光口误码秒
     	"
     	::= { rcftRemotePdhPortEntry 5 }

     rcftRemotePdhPortSECSCnt	OBJECT-TYPE
     	SYNTAX	INTEGER
     	MAX-ACCESS	read-only
     	STATUS	current
     	DESCRIPTION
     	"
     		pdh光口严重误码秒
     	"
     	::= { rcftRemotePdhPortEntry 6 }

    rcftRemotePdhPortLoopStatus   OBJECT-TYPE
     	SYNTAX	INTEGER
     	MAX-ACCESS	read-only
     	STATUS	current
     	DESCRIPTION
     	"
     		环回状态
     		1:本地环回，2：无本地环回，3：远端环回，4：无远端环回，
       	     5:无环回，
       	     6：本地内环使能，7：本地外环使能，8：本地双向环使能，
       	     9:远端内环使能，10：远端外环使能，11：远端双向环使能，
       	     12：本地内环禁止，13:本地外环禁止，14：本地双向环禁止，
       	     15：远端内环禁止，16：远端外环禁止，17：远端双向环禁止，

     	"
     	::= { rcftRemotePdhPortEntry 7 }

    rcftRemotePdhPortOrder  OBJECT-TYPE
     	SYNTAX	INTEGER
     	MAX-ACCESS	read-write
     	STATUS	current
     	DESCRIPTION
     	"
     			1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
				22: 端口BERT测试开始
				23: 端口BERT测试结束

     	"
        ::= { rcftRemotePdhPortEntry 8 }

     rcftRemotePdhPortBertStatus  OBJECT-TYPE
     	SYNTAX	INTEGER
     	MAX-ACCESS	read-only
     	STATUS	current
     	DESCRIPTION
     	"
     	   1: 误码仪使能
		   2: 误码仪禁止

     	"
        ::= { rcftRemotePdhPortEntry 9 }

	 rcftRemotePdhPortBertErrCode		OBJECT-TYPE
	    SYNTAX	Unsigned32
	    MAX-ACCESS	read-only
	    STATUS	current
	    DESCRIPTION
	    "
	      误码率方式:误码数，单位是bit
	    "
	    ::= { rcftRemotePdhPortEntry 10}


    --------------------------Pdh端口的告警------------------------

       rcftRemotePdhPortLOSTrap	NOTIFICATION-TYPE
      	OBJECTS{
			rcftRemotePdhPortAlarmStatus
      	}
      	STATUS current
     	DESCRIPTION
     	"
     		局端设备上Pdh端口的接收信号丢失告警
     	"
     	::= { rcftRemotePdhPortTraps 1 }


       rcftRemotePdhPortLOFTrap	NOTIFICATION-TYPE
      	OBJECTS{
			rcftRemotePdhPortAlarmStatus
      	}
      	STATUS current
     	DESCRIPTION
     	"
     		局端设备上Pdh端口的接收信号LOF告警
     	"
     	::= { rcftRemotePdhPortTraps 2 }


       rcftRemotePdhPortE3Trap	NOTIFICATION-TYPE
      	OBJECTS{
			rcftRemotePdhPortAlarmStatus
      	}
      	STATUS current
     	DESCRIPTION
     	"
     		局端设备上Pdh端口的E3告警
     	"
     	::= { rcftRemotePdhPortTraps 3 }

       rcftRemotePdhPortE6Trap	NOTIFICATION-TYPE
      	OBJECTS{
			rcftRemotePdhPortAlarmStatus
      	}
      	STATUS current
     	DESCRIPTION
     	"
     		局端设备上Pdh端口的E6告警
     	"
     	::= { rcftRemotePdhPortTraps 4 }

       rcftRemotePdhPortToLLOSTrap	NOTIFICATION-TYPE
      	OBJECTS{
			rcftRemotePdhPortAlarmStatus
      	}
      	STATUS current
     	DESCRIPTION
     	"
     		从本地设备上查看到的对端设备光口的接收信号丢失告警
     	"
     	::= { rcftRemotePdhPortTraps 5 }


       rcftRemotePdhPortToLLOFTrap	NOTIFICATION-TYPE
      	OBJECTS{
			rcftRemotePdhPortAlarmStatus
      	}
      	STATUS current
     	DESCRIPTION
     	"
     		从本地设备上查看到的对端设备光口的接收信号LOF告警
     	"
     	::= { rcftRemotePdhPortTraps 6 }


       rcftRemotePdhPortToLE3Trap	NOTIFICATION-TYPE
      	OBJECTS{
			rcftRemotePdhPortAlarmStatus
      	}
      	STATUS current
     	DESCRIPTION
     	"
     		从本地设备上查看到的对端设备光口的E3告警
     	"
     	::= { rcftRemotePdhPortTraps 7 }

       rcftRemotePdhPortToLE6rap	NOTIFICATION-TYPE
      	OBJECTS{
			rcftRemotePdhPortAlarmStatus
      	}
      	STATUS current
     	DESCRIPTION
     	"
     		从本地设备上查看到的对端设备光口的E6告警
     	"
     	::= { rcftRemotePdhPortTraps 8 }

     rcftRemotePdhPortToRPowerDown	NOTIFICATION-TYPE
      	OBJECTS{
			rcftRemotePdhPortAlarmStatus
      	}
      	STATUS current
     	DESCRIPTION
     	"
     		从本地设备上查看到的对端设备掉电告警
     	"
     	::= { rcftRemotePdhPortTraps 9 }


   --------------------------DS1端口的对象---------------------------------

   rcftRemoteDS1PortTable OBJECT-TYPE
       SYNTAX  SEQUENCE OF RcftRemoteDS1PortEntry
       MAX-ACCESS  not-accessible
       STATUS  current
       DESCRIPTION
       "
         The DS1 PORT table.
       "
       ::= { rcftRemoteDS1PortObjects 1 }

    rcftRemoteDS1PortEntry OBJECT-TYPE
       SYNTAX  RcftRemoteDS1PortEntry
       MAX-ACCESS  not-accessible
       STATUS  current
       DESCRIPTION
       "
          An entry in the DS1 PORT table.

       "
       INDEX   { rcftChassisIndex, rcftSlotIndex,
        			rcftRemoteDeviceIndex,rcftRemoteDS1PortIndex }
       ::= { rcftRemoteDS1PortTable 1 }


    RcftRemoteDS1PortEntry ::=
       SEQUENCE {
       rcftRemoteDS1PortIndex		 	Integer32,
       rcftRemoteDS1PortAlarmStatus	INTEGER,
       rcftRemoteDS1PortStatus		INTEGER,
       rcftRemoteDS1PortESCont		INTEGER,
       rcftRemoteDS1PortSESCont     INTEGER,
       rcftRemoteDS1PortBertStatus	INTEGER,
       rcftRemoteDS1PortFaultPass		INTEGER,
       rcftRemoteDS1PortLoopStatus	INTEGER,
       rcftRemoteDS1PortOrder			INTEGER,
       rcftRemoteDS1PortTranLength		INTEGER,
       rcftRemoteDS1PortFaultPassIndicator		INTEGER,
       rcftRemoteDS1PortframeType	INTEGER,
       rcftRemoteDS1PortChannel 	INTEGER

       }

    rcftRemoteDS1PortIndex OBJECT-TYPE
    	SYNTAX	   Integer32
    	MAX-ACCESS read-only
    	STATUS		current
    	DESCRIPTION
    	"
    		DS1口的索引
    	"
        ::= { rcftRemoteDS1PortEntry 1 }


    rcftRemoteDS1PortAlarmStatus	OBJECT-TYPE
    	SYNTAX	INTEGER
    	MAX-ACCESS read-only
    	STATUS		current
    	DESCRIPTION
    	"
    		BIT22：从本地设备上看对端DS1电口的LOF
			BIT21：从本地设备上看对端DS1电口的CRC
			BIT17：从本地设备上看对端DS1电口的LOS
			BIT16：从本地设备上看对端DS1电口的AIS

			BIT8	RED						  1:正常    0：告警
    	 	BIT7    YEL   					  1:正常    0：告警
			BIT6：LOF 接收信号帧失步告警
			BIT5：CRC CRC校验错告警
			BIT4    LCV   编码冲突告警       1：正常    0：告警
			BIT3    DMO   发送信号无输出     1：正常    0：告警
			BIT1：LOS 接收信号丢失告警
			BIT0：AIS 接收信号AIS 告警
    	"
        ::= { rcftRemoteDS1PortEntry 2 }


	rcftRemoteDS1PortStatus	OBJECT-TYPE
		SYNTAX	INTEGER
		MAX-ACCESS read-write
		STATUS	current
		DESCRIPTION
		"
				BIT0：线路编码类型   1:B8ZS       0:AMI
				BIT1: DS1是否成帧    1:成帧       0:非成帧
				BIT2: DS1是否打开    1：打开      0：关闭
		"
		::= { rcftRemoteDS1PortEntry 3 }

	rcftRemoteDS1PortESCont	  OBJECT-TYPE
		SYNTAX  INTEGER
		MAX-ACCESS	read-only
		STATUS  current
		DESCRIPTION
		"
			误码秒个数
		"
        ::= { rcftRemoteDS1PortEntry 4 }

    rcftRemoteDS1PortSESCont	  OBJECT-TYPE
		SYNTAX  INTEGER
		MAX-ACCESS	read-only
		STATUS  current
		DESCRIPTION
		"
			严重误码秒个数
		"
        ::= { rcftRemoteDS1PortEntry 5 }


	rcftRemoteDS1PortBertStatus	OBJECT-TYPE
		SYNTAX  INTEGER
		MAX-ACCESS	read-only
		STATUS	current
		DESCRIPTION
		"
		1: 误码仪使能
		2: 误码仪禁止
		"
		::= { rcftRemoteDS1PortEntry 6 }

     rcftRemoteDS1PortFaultPass   OBJECT-TYPE
		SYNTAX  INTEGER
		MAX-ACCESS	read-write
		STATUS	current
		DESCRIPTION
		"
		1: 故障转移使能
		2: 故障转移禁止
		"
        ::= { rcftRemoteDS1PortEntry 7 }

 	  rcftRemoteDS1PortLoopStatus  OBJECT-TYPE
		 SYNTAX  INTEGER
		 MAX-ACCESS	read-only
		 STATUS	current
		 DESCRIPTION
		 "
		  	1: 本地环回，
			2：无本地环回，
			3：远端环回，
			4：无远端环回，
			5: 无环回，
			6：本地内环使能，
			7：本地外环使能，
			8：本地双向环使能，
			9：远端内环使能，
			10：远端外环使能，
			11：远端双向环使能，
			12：本地内环禁止，
			13: 本地外环禁止，
			14：本地双向环禁止，
			5： 远端内环禁止，
			16：远端外环禁止，
			17：远端双向环禁止，
		 "
         ::= { rcftRemoteDS1PortEntry 8 }


      rcftRemoteDS1PortOrder  OBJECT-TYPE
		  SYNTAX  INTEGER
		  MAX-ACCESS	read-write
		  STATUS	current
		  DESCRIPTION
		  "
		 		1：硬复位
				2：软复位
				3：开始查询统计信息
				4：结束查询统计信息
				5：内环使能
				6：内环禁止
				7：外环使能
				8：外环禁止
				9: 无环回
				10: 本地内环使能
				11: 本地外环使能
				12: 本地双向环使能
				13: 远端内环使能
				14: 远端外环使能
				15: 远端双向环使能
				16: 本地内环禁止
				17: 本地外环禁止
				18: 本地双向环禁止
				19: 远端内环禁止
				20: 远端外环禁止
				21: 远端双向环禁止
 				22: 端口BERT测试开始
 				23: 端口BERT测试结束
		"
         ::= { rcftRemoteDS1PortEntry 9 }

    rcftRemoteDS1PortTranLength   OBJECT-TYPE
		  SYNTAX  INTEGER
		  MAX-ACCESS	read-write
		  STATUS	current
		  DESCRIPTION
		  "
		     DS1传输距离配置
		  "
         ::= { rcftRemoteDS1PortEntry 10 }

     rcftRemoteDS1PortFaultPassIndicator OBJECT-TYPE
		  SYNTAX  INTEGER
		  MAX-ACCESS	read-only
		  STATUS	current
		  DESCRIPTION
		  "
		     故障转移指示灯
		     １：灭，故障转移禁止
			 ２：绿常亮，故障转移使能，但没有故障发生
			 ３：黄闪亮，故障转移使能，且发生故障导致以太口关闭

		  "
		  ::= { rcftRemoteDS1PortEntry 11 }

     rcftRemoteDS1PortframeType	  OBJECT-TYPE
		  SYNTAX  INTEGER
		  MAX-ACCESS	read-write
		  STATUS	current
		  DESCRIPTION
		  "
		     帧格式
			1：SF帧格式
			2：ESF
			3：DM
			4：SLC-96

		  "
		  ::= { rcftRemoteDS1PortEntry 12 }

     rcftRemoteDS1PortChannel	 OBJECT-TYPE
		  SYNTAX  INTEGER
		  MAX-ACCESS	read-write
		  STATUS	current
		  DESCRIPTION
		  "
		     成帧时所用的时隙，bit0-bit30每位分别表示时隙１到31的占用情况。
		  "
		  ::= { rcftRemoteDS1PortEntry 13 }




     --------------------------DS1端口的流量统计------------------------


         rcftRemoteDS1StatisticTable OBJECT-TYPE
	        SYNTAX SEQUENCE OF RcftRemoteDS1StatisticEntry
	        MAX-ACCESS not-accessible
	        STATUS current
	        DESCRIPTION
	          "
	          局端设备DS1端口的统计表.
	          "
            ::= {rcftRemoteDS1PortPerformance 1}


	    rcftRemoteDS1StatisticEntry OBJECT-TYPE
	        SYNTAX RcftRemoteDS1StatisticEntry
	        MAX-ACCESS not-accessible
	        STATUS current
	        DESCRIPTION
	          "
	             以rcftRemoteDS1Index为索引
	          "
	        AUGMENTS { rcftRemoteDS1PortEntry }
	        ::= {rcftRemoteDS1StatisticTable 1}

	    RcftRemoteDS1StatisticEntry ::= SEQUENCE {
				rcftRemoteDS1TxPackets       Counter32,
				rcftRemoteDS1TxBytes           Counter32,
				rcftRemoteDS1TxFailurePackets   Counter32,
				rcftRemoteDS1RxPackets         Counter32,
				rcftRemoteDS1RxBytes           Counter32,
				rcftRemoteDS1RxErrorPackets    Counter32,
				rcftRemoteDS1FluxTimer	Counter32
	         }


    	  rcftRemoteDS1TxPackets OBJECT-TYPE
					SYNTAX Counter32
					MAX-ACCESS read-only
					STATUS current
					DESCRIPTION
						"
							DS1口发送以太网包数
						"
					::= { rcftRemoteDS1StatisticEntry 1 }

		rcftRemoteDS1TxBytes OBJECT-TYPE
					SYNTAX Counter32
					MAX-ACCESS read-only
					STATUS current
					DESCRIPTION
						"
							DS1口发送以太网字节数
						"
					::= { rcftRemoteDS1StatisticEntry 2 }


	    rcftRemoteDS1TxFailurePackets OBJECT-TYPE
					SYNTAX Counter32
					MAX-ACCESS read-only
					STATUS current
					DESCRIPTION
						"
							DS1电口发送以太网丢包数
						"
					::= { rcftRemoteDS1StatisticEntry 3 }

		 rcftRemoteDS1RxPackets OBJECT-TYPE
					SYNTAX Counter32
					MAX-ACCESS read-only
					STATUS current
					DESCRIPTION
						"
							DS1口接收以太网包数
						"
					::= { rcftRemoteDS1StatisticEntry 4 }

		 rcftRemoteDS1RxBytes OBJECT-TYPE
					SYNTAX Counter32
					MAX-ACCESS read-only
					STATUS current
					DESCRIPTION
						"
							DS1口接收以太网字节数
						"
					::= { rcftRemoteDS1StatisticEntry 5 }

	    rcftRemoteDS1RxErrorPackets OBJECT-TYPE
					SYNTAX Counter32
					MAX-ACCESS read-only
					STATUS current
					DESCRIPTION
						"
							DS1电口接收以太网丢包数
						"
					::= { rcftRemoteDS1StatisticEntry 6 }

        rcftRemoteDS1FluxTimer	OBJECT-TYPE
        			SYNTAX		Counter32
        			MAX-ACCESS 	read-only
        			STATUS		current
        			DESCRIPTION
        				"
        					流量统计的时间
        				"
                    ::= { rcftRemoteDS1StatisticEntry 7 }



     --------------------------DS1端口的告警------------------------

       rcftRemoteDS1PortAISTrap	NOTIFICATION-TYPE
      	OBJECTS{
			rcftRemoteDS1PortAlarmStatus
      	}
      	STATUS current
     	DESCRIPTION
     	"
     		本端设备上DS1端口的接收信号AIS告警
     	"
     	::= { rcftRemoteDS1PortTraps 1 }


       rcftRemoteDS1PortLOSTrap	NOTIFICATION-TYPE
      	OBJECTS{
			rcftRemoteDS1PortAlarmStatus
      	}
      	STATUS current
     	DESCRIPTION
     	"
     		本端设备上DS1端口的接收信号丢失告警
     	"
     	::= { rcftRemoteDS1PortTraps 2 }

       rcftRemoteDS1PortToLAISTrap	NOTIFICATION-TYPE
      	OBJECTS{
			rcftRemoteDS1PortAlarmStatus
      	}
      	STATUS current
     	DESCRIPTION
     	"
     		本端设备上DS1端口的接收对端信号AIS告警
     	"
     	::= { rcftRemoteDS1PortTraps 3 }


       rcftRemoteDS1PortToLLOSTrap	NOTIFICATION-TYPE
      	OBJECTS{
			rcftRemoteDS1PortAlarmStatus
      	}
      	STATUS current
     	DESCRIPTION
     	"
     		本端设备上DS1端口的接收对端信号丢失告警
     	"
     	::= { rcftRemoteDS1PortTraps 4 }


		rcftRemoteDS1PortLOFTrap	NOTIFICATION-TYPE
      	OBJECTS{
			rcftRemoteDS1PortAlarmStatus
      	}
      	STATUS current
     	DESCRIPTION
     	"
     		本端设备上DS1端口的接收信号LOF告警
     	"
     	::= { rcftRemoteDS1PortTraps 5 }


       rcftRemoteDS1PortCRCTrap	NOTIFICATION-TYPE
      	OBJECTS{
			rcftRemoteDS1PortAlarmStatus
      	}
      	STATUS current
     	DESCRIPTION
     	"
     		本端设备上DS1端口的接收信号CRC告警
     	"
     	::= { rcftRemoteDS1PortTraps 6 }

       rcftRemoteDS1PortToLLOFTrap	NOTIFICATION-TYPE
      	OBJECTS{
			rcftRemoteDS1PortAlarmStatus
      	}
      	STATUS current
     	DESCRIPTION
     	"
     		本端设备上DS1端口的接收对端信号LOF告警
     	"
     	::= { rcftRemoteDS1PortTraps 7 }


       rcftRemoteDS1PortToLCRCTrap	NOTIFICATION-TYPE
      	OBJECTS{
			rcftRemoteDS1PortAlarmStatus
      	}
      	STATUS current
     	DESCRIPTION
     	"
     		本端设备上DS1端口的接收对端信号CRC告警
     	"
     	::= { rcftRemoteDS1PortTraps 8 }

     	rcftRemoteDS1PortFaultPassIndicatorTrap	NOTIFICATION-TYPE
      	OBJECTS{
			rcftRemoteDS1PortFaultPassIndicator
      	}
      	STATUS current
     	DESCRIPTION
     	"
     		１：灭，故障转移禁止
			２：绿常亮，故障转移使能，但没有故障发生
			３：黄闪亮，故障转移使能，且发生故障导致以太口关闭
     	"
     	::= { rcftRemoteDS1PortTraps 9 }

     	rcftRemoteDS1PortDMOTrap	NOTIFICATION-TYPE
      	OBJECTS{
			rcftRemoteDS1PortAlarmStatus
      	}
      	STATUS current
     	DESCRIPTION
     	"
     		本端设备上DS1端口的接收信号DMO告警
     	"
     	::= { rcftRemoteDS1PortTraps 10 }


       rcftRemoteDS1PortCVTrap	NOTIFICATION-TYPE
      	OBJECTS{
			rcftRemoteDS1PortAlarmStatus
      	}
      	STATUS current
     	DESCRIPTION
     	"
     		本端设备上DS1端口的CV告警
     	"
     	::= { rcftRemoteDS1PortTraps 11 }

       rcftRemoteDS1PortYELTrap	NOTIFICATION-TYPE
      	OBJECTS{
			rcftRemoteDS1PortAlarmStatus
      	}
      	STATUS current
     	DESCRIPTION
     	"
     		本端设备上DS1端口的YEL告警
     	"
     	::= { rcftRemoteDS1PortTraps 12 }


       rcftRemoteDS1PortREDTrap	NOTIFICATION-TYPE
      	OBJECTS{
			rcftRemoteDS1PortAlarmStatus
      	}
      	STATUS current
     	DESCRIPTION
     	"
     		本端设备上DS1端口的RED告警
     	"
     	::= { rcftRemoteDS1PortTraps 13 }



   --------------------------子卡的对象---------------------------------

     rcftRemoteMoudleTable OBJECT-TYPE
       SYNTAX  SEQUENCE OF RcftRemoteMoudleEntry
       MAX-ACCESS  not-accessible
       STATUS  current
       DESCRIPTION
       "
         The EthFe PORT of Moudle table.
       "
       ::= { rcftRemoteMoudleObjects 1 }

    rcftRemoteMoudleEntry OBJECT-TYPE
       SYNTAX  RcftRemoteMoudleEntry
       MAX-ACCESS  not-accessible
       STATUS  current
       DESCRIPTION
       "
          An entry in the EthFe PORT table.

       "
       INDEX   { rcftChassisIndex, rcftSlotIndex,
       			 rcftRemoteDeviceIndex, rcftRemoteMoudleIndex }
       ::= { rcftRemoteMoudleTable 1 }


    RcftRemoteMoudleEntry ::=
       SEQUENCE {
       rcftRemoteMoudleIndex	Integer32,
       rcftRemoteMoudleExist		INTEGER,
       rcftRemoteMoudleType			INTEGER,
       rcftRemoteMoudleStatus		INTEGER,
	   rcftRemoteMoudleSigleChipDescr	OCTET STRING,
	   rcftRemoteMoudleHardWareDescr	OCTET STRING,
	   rcftRemoteMoudleFPGADescr		OCTET STRING,
       rcftRemoteMoudleOrder			INTEGER,
       rcftRemoteMoudleIFOrder			OCTET STRING
       }


    rcftRemoteMoudleIndex OBJECT-TYPE
    	SYNTAX	   Integer32
    	MAX-ACCESS read-only
    	STATUS		current
    	DESCRIPTION
    	"
    		EthFe口的索引
    	"
        ::= { rcftRemoteMoudleEntry 1 }

    rcftRemoteMoudleExist OBJECT-TYPE
        SYNTAX INTEGER
        {
            exist(1),
            notExist(2)
        }
        MAX-ACCESS read-only
        STATUS current
        DESCRIPTION
          "
          槽位板卡存在状态(1:存在,2:不存在).
          "
        ::= {rcftRemoteMoudleEntry 2}


    rcftRemoteMoudleType OBJECT-TYPE
        SYNTAX      INTEGER
        {
           e-SUBM-2E1-A(6402),
           e-SUBM-2FV35-A(6422),
           e-SUBM-2FE-A(6423),
           e-SUBM-FE4E1-A(6424),
           e-SUBM-FV35-A(6425),
           e-SUBM-FV35-B(6427),
           e-SUBM-2FV35-B(6428)
        }
    	MAX-ACCESS	read-write
    	STATUS		current
    	DESCRIPTION
    	"
   	       模块类型号
   	       6402:   E-SUBM-2E1-A
   	       6422:   E-SUBM-2FV35-A
   	       6423:   E-SUBM-2FE-A
   	       6424:   E-SUBM-FE4E1-A
   	       6425:   E-SUBM-FV35-A
   	       6427:   E-SUBM-FV35-B
   	       6428:   E-SUBM-2FV35-B

   	       注意：为了网管实现的方便，子卡的设备类型号0x1901~0x19FE
   	       因此子卡的设备类型号，将在 6401~6654 之间。

    	"
 		::= { rcftRemoteMoudleEntry 3 }

    rcftRemoteMoudleStatus OBJECT-TYPE
    	SYNTAX		INTEGER
    	MAX-ACCESS	read-write
    	STATUS		current
    	DESCRIPTION
    	"
			BIT0    误码率超过10-3时，是否切断E1     0：不切断   1：切断
    	"
 		::= { rcftRemoteMoudleEntry 4 }

    rcftRemoteMoudleSigleChipDescr OBJECT-TYPE
    	SYNTAX		OCTET STRING (SIZE (0..30))
    	MAX-ACCESS	read-only
    	STATUS		current
    	DESCRIPTION
    	"
        A textual description of the siglechip program version.
    	"
 		::= { rcftRemoteMoudleEntry 5 }

    rcftRemoteMoudleHardWareDescr OBJECT-TYPE
    	SYNTAX		OCTET STRING (SIZE (0..30))
    	MAX-ACCESS	read-only
    	STATUS		current
    	DESCRIPTION
    	"
        A textual description of the siglechip program version.
    	"
 		::= { rcftRemoteMoudleEntry 6 }

    rcftRemoteMoudleFPGADescr OBJECT-TYPE
    	SYNTAX		OCTET STRING (SIZE (0..30))
    	MAX-ACCESS	read-only
    	STATUS		current
    	DESCRIPTION
    	"
        A textual description of the FPGA program version.
    	"
 		::= { rcftRemoteMoudleEntry 7 }

	rcftRemoteMoudleOrder	OBJECT-TYPE
	  	SYNTAX	INTEGER
		MAX-ACCESS	read-write
		STATUS	current
		DESCRIPTION
		"
			子卡的命令,属于子卡中模块级的命令.

			1: 复位设备
			2: 复位以太网芯片
			3: 流量统计查询开始
			4: 流量统计查询结束
		"
        ::={ rcftRemoteMoudleEntry 8}

	rcftRemoteMoudleIFOrder	OBJECT-TYPE
	  	SYNTAX		OCTET STRING (SIZE (0..30))
		MAX-ACCESS	read-write
		STATUS	current
		DESCRIPTION
		"
			子卡的命令,属于子卡中接口级的命令.

			此命令节点采用字节块的方式下发,每一个字节表示一个端口.
			其中,每一个字节的数值表示如下:

			0: 无环回
			1: 误码仪功能使能
			2: 误码仪功能禁止
			3: 本地E1外环使能
			4: 本地E1内环使能
			5: 本地V35内环使能
			6: 远端V35内环使能
			7: 本地E1外环禁止

		"
        ::={ rcftRemoteMoudleEntry 9}


   rcftRemoteMoudleExistTrap	NOTIFICATION-TYPE
      OBJECTS{
		rcftRemoteMoudleExist
      }
      STATUS current
     DESCRIPTION
     "
     	模块在位告警告警
     "
     ::= { rcftRemoteMoudleTraps 1 }

   --------------------------以太网电口的对象-----------------------------
    rcftRemoteMoudleEthFeTable OBJECT-TYPE
       SYNTAX  SEQUENCE OF RcftRemoteMoudleEthFeEntry
       MAX-ACCESS  not-accessible
       STATUS  current
       DESCRIPTION
       "
         The EthFe PORT of Moudle table.
       "
       ::= { rcftRemoteMoudleEthFeObjects 1 }

    rcftRemoteMoudleEthFeEntry OBJECT-TYPE
       SYNTAX  RcftRemoteMoudleEthFeEntry
       MAX-ACCESS  not-accessible
       STATUS  current
       DESCRIPTION
       "
          An entry in the EthFe PORT table.

       "
       INDEX   { rcftChassisIndex, rcftSlotIndex,
       			 rcftRemoteDeviceIndex, rcftRemoteMoudleIndex,
       			 rcftRemoteMoudleEthFeIndex }
       ::= { rcftRemoteMoudleEthFeTable 1 }


    RcftRemoteMoudleEthFeEntry ::=
       SEQUENCE {
       rcftRemoteMoudleEthFeIndex	Integer32,
       rcftRemoteMoudleEthFeStatus			INTEGER,
       rcftRemoteMoudleEthFeRxRestrictSpeed	INTEGER,
       rcftRemoteMoudleEthFeTxRestrictSpeed	INTEGER,
       rcftRemoteMoudleEthFeRestrictSpeedStep INTEGER,
       rcftRemoteMoudleEthFeAlarmStatus	INTEGER
       }

    rcftRemoteMoudleEthFeIndex OBJECT-TYPE
    	SYNTAX	   Integer32
    	MAX-ACCESS read-only
    	STATUS		current
    	DESCRIPTION
    	"
    		EthFe口的索引
    	"
        ::= { rcftRemoteMoudleEthFeEntry 1 }

    rcftRemoteMoudleEthFeStatus OBJECT-TYPE
    	SYNTAX		INTEGER
    	MAX-ACCESS	read-write
    	STATUS		current
    	DESCRIPTION
    	"

    	    BIT6	以太网电口的流量控制 0：禁止；   1：使能
			BIT5	以太网电口的时钟方式 0：从时钟；   1：主时钟
			BIT4	以太网电口的自适应	 0：自适应关闭；   1：自适应打开
			BIT3	以太网电口的使能	 0：关闭；   1：打开
			BIT2	以太网电口的link状态 0：link down； 1：link up
			BIT1    以太网电口的速率   	 0：10M      1：100M
			BIT0    以太网电口的双工     0：半双工   1：全双工
    	"
 		::= { rcftRemoteMoudleEthFeEntry 2 }

 	rcftRemoteMoudleEthFeRxRestrictSpeed  OBJECT-TYPE
    	SYNTAX		INTEGER
    	MAX-ACCESS	read-write
    	STATUS		current
    	DESCRIPTION
    	"
             接收带宽
    	"
 		::= { rcftRemoteMoudleEthFeEntry 3 }

 	rcftRemoteMoudleEthFeTxRestrictSpeed  OBJECT-TYPE
    	SYNTAX		INTEGER
    	MAX-ACCESS	read-write
    	STATUS		current
    	DESCRIPTION
    	"
           发送带宽
       	"
 		::= { rcftRemoteMoudleEthFeEntry 4 }

 	rcftRemoteMoudleEthFeRestrictSpeedStep	OBJECT-TYPE
 		SYNTAX	INTEGER
 		MAX-ACCESS	read-only
 		STATUS		current
 		DESCRIPTION
 		"
 			带宽粒度
 			0x00：64Kbps；0x01：32Kbps（无）；其余：保留。
 		"
 	    ::= { rcftRemoteMoudleEthFeEntry 5 }

    rcftRemoteMoudleEthFeAlarmStatus	OBJECT-TYPE
    	SYNTAX	INTEGER
    	MAX-ACCESS read-only
    	STATUS		current
    	DESCRIPTION
    	"
			BIT0	本地以太网CRC错误告警		0：告警；        1：正常
    	"
        ::= { rcftRemoteMoudleEthFeEntry 6 }

    --------------------------以太网电口的流量统计--------------------------

         rcftRemoteMoudleEthFeStatisticTable OBJECT-TYPE
	        SYNTAX SEQUENCE OF RcftRemoteMoudleEthFeStatisticEntry
	        MAX-ACCESS not-accessible
	        STATUS current
	        DESCRIPTION
	          "
	          局端设备Eth端口的统计表.
	          "
            ::= {rcftRemoteMoudleEthFePerformance 1}

	    rcftRemoteMoudleEthFeStatisticEntry OBJECT-TYPE
	        SYNTAX RcftRemoteMoudleEthFeStatisticEntry
	        MAX-ACCESS not-accessible
	        STATUS current
	        DESCRIPTION
	          "
	             以rcftRemoteMoudleEthFeIndex为索引
	          "
	        AUGMENTS { rcftRemoteMoudleEthFeEntry }
	        ::= {rcftRemoteMoudleEthFeStatisticTable 1}

	    RcftRemoteMoudleEthFeStatisticEntry ::= SEQUENCE {
				rcftRemoteMoudleEthFeTxPackets         Counter32,
				rcftRemoteMoudleEthFeTxBytes           Counter32,
				rcftRemoteMoudleEthFeTxFailurePackets  Counter32,
				rcftRemoteMoudleEthFeRxPackets         Counter32,
				rcftRemoteMoudleEthFeRxBytes           Counter32,
				rcftRemoteMoudleEthFeRxErrorPackets    Counter32,
				rcftRemoteMoudleEthFeFluxTimer		   Counter32
	         }


    	  rcftRemoteMoudleEthFeTxPackets OBJECT-TYPE
					SYNTAX Counter32
					MAX-ACCESS read-only
					STATUS current
					DESCRIPTION
						"
							以太网口发送以太网包数
						"
					::= { rcftRemoteMoudleEthFeStatisticEntry 1 }

		 rcftRemoteMoudleEthFeTxBytes OBJECT-TYPE
					SYNTAX Counter32
					MAX-ACCESS read-only
					STATUS current
					DESCRIPTION
						"
							以太网口发送以太网字节数
						"
					::= { rcftRemoteMoudleEthFeStatisticEntry 2 }


	    rcftRemoteMoudleEthFeTxFailurePackets OBJECT-TYPE
					SYNTAX Counter32
					MAX-ACCESS read-only
					STATUS current
					DESCRIPTION
						"
							以太网电口发送以太网丢包数
						"
					::= { rcftRemoteMoudleEthFeStatisticEntry 3 }

		 rcftRemoteMoudleEthFeRxPackets OBJECT-TYPE
					SYNTAX Counter32
					MAX-ACCESS read-only
					STATUS current
					DESCRIPTION
						"
							以太网口接收以太网包数
						"
					::= { rcftRemoteMoudleEthFeStatisticEntry 4 }

		 rcftRemoteMoudleEthFeRxBytes OBJECT-TYPE
					SYNTAX Counter32
					MAX-ACCESS read-only
					STATUS current
					DESCRIPTION
						"
							以太网口接收以太网字节数
						"
					::= { rcftRemoteMoudleEthFeStatisticEntry 5 }

	    rcftRemoteMoudleEthFeRxErrorPackets OBJECT-TYPE
					SYNTAX Counter32
					MAX-ACCESS read-only
					STATUS current
					DESCRIPTION
						"
							以太网电口接收以太网丢包数
						"
					::= { rcftRemoteMoudleEthFeStatisticEntry 6 }

        rcftRemoteMoudleEthFeFluxTimer	OBJECT-TYPE
        			SYNTAX		Counter32
        			MAX-ACCESS 	read-only
        			STATUS		current
        			DESCRIPTION
        				"
        					流量统计的时间
        				"
                    ::= { rcftRemoteMoudleEthFeStatisticEntry 7 }


    --------------------------以太网电口的告警--------------------------

       rcftRemoteMoudleEthFeLinkTrap	NOTIFICATION-TYPE
      	OBJECTS{
			rcftRemoteMoudleEthFeStatus
      	}
      	STATUS current
     	DESCRIPTION
     	"
     		局端设备上以太网电口的LINK告警
     	"
     	::= { rcftRemoteMoudleEthFeTraps 1 }

   --------------------------PDH端口的对象---------------------------------

    rcftRemoteMoudlePdhTable OBJECT-TYPE
       SYNTAX  SEQUENCE OF RcftRemoteMoudlePdhEntry
       MAX-ACCESS  not-accessible
       STATUS  current
       DESCRIPTION
       "
         The Pdh PORT table.
       "
       ::= { rcftRemoteMoudlePdhObjects 1 }

    rcftRemoteMoudlePdhEntry OBJECT-TYPE
       SYNTAX  RcftRemoteMoudlePdhEntry
       MAX-ACCESS  not-accessible
       STATUS  current
       DESCRIPTION
       "
          An entry in the Pdh PORT table.

       "
       INDEX   { rcftChassisIndex, rcftSlotIndex,
                 rcftRemoteDeviceIndex, rcftRemoteMoudleIndex,
       			 rcftRemoteMoudlePdhIndex }
       ::= { rcftRemoteMoudlePdhTable 1 }


    RcftRemoteMoudlePdhEntry ::=
       SEQUENCE {
       rcftRemoteMoudlePdhIndex		 	Integer32,
       rcftRemoteMoudlePdhAlarmStatus		INTEGER,
       rcftRemoteMoudlePdhStatus		 	INTEGER
       }

    rcftRemoteMoudlePdhIndex OBJECT-TYPE
    	SYNTAX	   Integer32
    	MAX-ACCESS read-only
    	STATUS		current
    	DESCRIPTION
    	"
    		Pdh口的索引
    	"
        ::= { rcftRemoteMoudlePdhEntry 1 }

     rcftRemoteMoudlePdhAlarmStatus OBJECT-TYPE
     	SYNTAX	INTEGER
     	MAX-ACCESS read-only
     	STATUS	current
    	DESCRIPTION
    	"
    		Pdh口的告警状态
    		其他位：保留
			BIT20	从本地设备上查看到的对端设备掉电告警	 0：告警； 1：正常
			BIT19	从本地设备上查看到的对端设备光口的E-6	 0：告警； 1：正常
			BIT18	从本地设备上查看到的对端设备光口的E-3	 0：告警； 1：正常
			BIT17	从本地设备上查看到的对端设备光口的LOF	 0：告警； 1：正常
			BIT16	从本地设备上查看到的对端设备光口的LOS	 0：告警； 1：正常

			BIT3	E-6 pdh光口的E-6告警 0：告警； 1：正常
			BIT2	E-3	pdh光口的E-3告警 0：告警； 1：正常
			BIT1    LOF pdh光口LOF告警   0：告警   1：正常
			BIT0    LOS pdh光口LOS告警   0：告警   1：正常
		"
        ::= { rcftRemoteMoudlePdhEntry 2 }

     rcftRemoteMoudlePdhStatus OBJECT-TYPE
     	SYNTAX	INTEGER
     	MAX-ACCESS read-write
     	STATUS	current
    	DESCRIPTION
    	"
    	"
        ::= { rcftRemoteMoudlePdhEntry 3 }

   --------------------------PDH端口的告警---------------------------------

    rcftRemoteMoudlePdhLOSTrap	NOTIFICATION-TYPE
      	OBJECTS{
			rcftRemoteMoudlePdhAlarmStatus
      	}
      	STATUS current
     	DESCRIPTION
     	"
     		局端设备上Pdh光口的LOS告警
     	"
     	::= { rcftRemoteMoudlePdhTraps 1 }

     rcftRemoteMoudlePdhLOFTrap	NOTIFICATION-TYPE
      	OBJECTS{
			rcftRemoteMoudlePdhAlarmStatus
      	}
      	STATUS current
     	DESCRIPTION
     	"
     		局端设备上Pdh光口的LOF告警
     	"
     	::= { rcftRemoteMoudlePdhTraps 2 }

   --------------------------E1端口的对象---------------------------------

    rcftRemoteMoudleE1Table OBJECT-TYPE
       SYNTAX  SEQUENCE OF RcftRemoteMoudleE1Entry
       MAX-ACCESS  not-accessible
       STATUS  current
       DESCRIPTION
       "
         The E1 PORT table.
       "
       ::= { rcftRemoteMoudleE1Objects 1 }

    rcftRemoteMoudleE1Entry OBJECT-TYPE
       SYNTAX  RcftRemoteMoudleE1Entry
       MAX-ACCESS  not-accessible
       STATUS  current
       DESCRIPTION
       "
          An entry in the E1 PORT table.

       "
       INDEX   { rcftChassisIndex, rcftSlotIndex,
                 rcftRemoteDeviceIndex, rcftRemoteMoudleIndex,
       			 rcftRemoteMoudleE1Index }
       ::= { rcftRemoteMoudleE1Table 1 }


    RcftRemoteMoudleE1Entry ::=
       SEQUENCE {
       rcftRemoteMoudleE1Index		 	Integer32,
       rcftRemoteMoudleE1AlarmStatus	INTEGER,
       rcftRemoteMoudleE1Status			INTEGER,
       rcftRemoteMoudleE1TimeSlots		INTEGER,
       rcftRemoteMoudleE1TS0Mode		INTEGER,
       rcftRemoteMoudleE1LoopStatus		INTEGER,
       rcftRemoteMoudleE1ESCnt			INTEGER,
       rcftRemoteMoudleE1SESCnt			INTEGER
       }

    rcftRemoteMoudleE1Index OBJECT-TYPE
    	SYNTAX	   Integer32
    	MAX-ACCESS read-only
    	STATUS		current
    	DESCRIPTION
    	"
    		E1口的索引
    	"
        ::= { rcftRemoteMoudleE1Entry 1 }

     rcftRemoteMoudleE1AlarmStatus OBJECT-TYPE
     	SYNTAX	INTEGER
     	MAX-ACCESS read-only
     	STATUS	current
    	DESCRIPTION
    	"
    		E1口的告警状态
    		其他位：保留

    		BIT21  	从本地设备上看到的对端设备E1的CRC告警：0：告警； 1：正常。
    		BIT20  	从本地设备上看到的对端设备E1的LOMF告警：0：告警； 1：正常。
    		BIT19  	从本地设备上看到的对端设备E1的LOF告警：0：告警； 1：正常。
    		BIT18  	从本地设备上看到的对端设备E1的CV告警：0：告警； 1：正常。
    		BIT17  	从本地设备上看到的对端设备E1的AIS告警：0：告警； 1：正常。
    		BIT16  	从本地设备上看到的对端设备E1的LOS告警：0：告警； 1：正常。


    		BIT5	CRC  0: 本地E1 CRC告警；   1：本地E1 CRC正常；
			BIT4	LOMF 0：本地E1 复帧失步；  1：本地E1 复帧正常。
			BIT3	LOF	 0：本地E1 帧失步；	   1：本地E1 帧正常。
			BIT2	CV	 0：本地HDB3 编码违例；1：本地HDB3 编码正常。
			BIT1	AIS	 0：本地AIS 告警；     1：无本地AIS 告警。
			BIT0	LOS	 0：本地信号消失告警； 1：本地信号正常。
    	"
        ::= { rcftRemoteMoudleE1Entry 2 }

     rcftRemoteMoudleE1Status OBJECT-TYPE
     	SYNTAX	INTEGER
     	MAX-ACCESS read-write
     	STATUS	current
    	DESCRIPTION
    	"
    		E1口的状态
    		其他位：保留

    		BIT14   本地E1口内环          0：禁止；        1：使能
    		BIT13   E1是否被网管禁止      0：正常；        1：禁止
    		BIT12   E1关断是否由延时引起  0：其他原因；    1：因为延时引起；
    		BIT11   E1口是否使用	 	  0：不使用；      1：使用；
    		BIT10   E1口建链是否成功	  0：不成功；      1：成功；
    		BIT9    对端的E1祯中是否包含CRC	  0：无CRC；      1：有CRC；
    		BIT8    故障转移功能	 0：禁止；      1：使能；
    		BIT7    是否使用SA bit	 0：不使用；    1：使用；
    		BIT6    CRC自协商结果	 0：禁止；      1：使能；
    		BIT5    误码测试功能	 0：禁止；      1：使能；
  			BIT4    误码测试结果	 0：有误码；      1：正常；
  			BIT3-2  时钟方式      	 00：从时钟； 01：保留； 10：V35终端时钟 11：主时钟
  			BIT1    时隙带宽控制     0：从控；      1：主控；
  			BIT0    OPEN             0：本地E1端口关闭；    1：本地E1端口打开；
    	"
        ::= { rcftRemoteMoudleE1Entry 3 }


      rcftRemoteMoudleE1TimeSlots  OBJECT-TYPE
      	SYNTAX	INTEGER
      	MAX-ACCESS  read-write
      	STATUS	current
      	DESCRIPTION
      	"
      		E1口在成帧模式下所占用的时隙,bit0-bit30每位分别表示时隙1到时隙31的占用情况。
      		时隙0的占用与否是通过透明成帧模式判断的。
      	"
        ::= { rcftRemoteMoudleE1Entry 4 }

      rcftRemoteMoudleE1TS0Mode  OBJECT-TYPE
      	SYNTAX  INTEGER
      	MAX-ACCESS read-write
      	STATUS	current
      	DESCRIPTION
		"
			工作模式（TS0）：
				1：透明；
				2：成帧
		"
        ::= { rcftRemoteMoudleE1Entry 5 }

      rcftRemoteMoudleE1LoopStatus  OBJECT-TYPE
       	SYNTAX	INTEGER
       	MAX-ACCESS read-only
       	STATUS	current
       	DESCRIPTION
       	"
       	     E1的环回状态：1:本地环回，2：无本地环回，3：远端环回，4：无远端环回，
						   5:无环回，
						   6：本地内环使能，7：本地外环使能，8：本地双向环使能，
						   9:远端内环使能，10：远端外环使能，11：远端双向环使能，
						   12：本地内环禁止，13:本地外环禁止，14：本地双向环禁止，
						   15：远端内环禁止，16：远端外环禁止，17：远端双向环禁止，
       	"
        ::= { rcftRemoteMoudleE1Entry 6 }

      rcftRemoteMoudleE1ESCnt OBJECT-TYPE
        SYNTAX INTEGER
        MAX-ACCESS read-only
        STATUS current
        DESCRIPTION
        "
        局端设备E1误码秒统计计数
        "
        ::= {rcftRemoteMoudleE1Entry 7}

      rcftRemoteMoudleE1SESCnt OBJECT-TYPE
        SYNTAX INTEGER
        MAX-ACCESS read-only
        STATUS current
        DESCRIPTION
        "
        局端设备E1严重误码秒统计计数
        "
        ::= {rcftRemoteMoudleE1Entry 8}

   --------------------------E1端口的流量统计---------------------------------

         rcftRemoteMoudleE1StatisticTable OBJECT-TYPE
	        SYNTAX SEQUENCE OF RcftRemoteMoudleE1StatisticEntry
	        MAX-ACCESS not-accessible
	        STATUS current
	        DESCRIPTION
	          "
	          局端设备E1端口的统计表.
	          "
            ::= {rcftRemoteMoudleE1Performance 1}

	    rcftRemoteMoudleE1StatisticEntry OBJECT-TYPE
	        SYNTAX RcftRemoteMoudleE1StatisticEntry
	        MAX-ACCESS not-accessible
	        STATUS current
	        DESCRIPTION
	          "
	             以rcftRemoteMoudleE1Index为索引
	          "
	        AUGMENTS { rcftRemoteMoudleE1Entry }
	        ::= {rcftRemoteMoudleE1StatisticTable 1}

	    RcftRemoteMoudleE1StatisticEntry ::= SEQUENCE {
				rcftRemoteMoudleE1TxPackets         Counter32,
				rcftRemoteMoudleE1TxBytes           Counter32,
				rcftRemoteMoudleE1TxFailurePackets  Counter32,
				rcftRemoteMoudleE1RxPackets         Counter32,
				rcftRemoteMoudleE1RxBytes           Counter32,
				rcftRemoteMoudleE1RxErrorPackets    Counter32,
				rcftRemoteMoudleE1FluxTimer		    Counter32
	         }


    	  rcftRemoteMoudleE1TxPackets OBJECT-TYPE
					SYNTAX Counter32
					MAX-ACCESS read-only
					STATUS current
					DESCRIPTION
						"
							E1口发送以太网包数
						"
					::= { rcftRemoteMoudleE1StatisticEntry 1 }

		 rcftRemoteMoudleE1TxBytes OBJECT-TYPE
					SYNTAX Counter32
					MAX-ACCESS read-only
					STATUS current
					DESCRIPTION
						"
							E1口发送以太网字节数
						"
					::= { rcftRemoteMoudleE1StatisticEntry 2 }


	    rcftRemoteMoudleE1TxFailurePackets OBJECT-TYPE
					SYNTAX Counter32
					MAX-ACCESS read-only
					STATUS current
					DESCRIPTION
						"
							E1口发送以太网丢包数
						"
					::= { rcftRemoteMoudleE1StatisticEntry 3 }

		 rcftRemoteMoudleE1RxPackets OBJECT-TYPE
					SYNTAX Counter32
					MAX-ACCESS read-only
					STATUS current
					DESCRIPTION
						"
							E1口接收以太网包数
						"
					::= { rcftRemoteMoudleE1StatisticEntry 4 }

		 rcftRemoteMoudleE1RxBytes OBJECT-TYPE
					SYNTAX Counter32
					MAX-ACCESS read-only
					STATUS current
					DESCRIPTION
						"
							E1接收以太网字节数
						"
					::= { rcftRemoteMoudleE1StatisticEntry 5 }

	    rcftRemoteMoudleE1RxErrorPackets OBJECT-TYPE
					SYNTAX Counter32
					MAX-ACCESS read-only
					STATUS current
					DESCRIPTION
						"
							E1口接收以太网丢包数
						"
					::= { rcftRemoteMoudleE1StatisticEntry 6 }

        rcftRemoteMoudleE1FluxTimer	OBJECT-TYPE
        			SYNTAX		Counter32
        			MAX-ACCESS 	read-only
        			STATUS		current
        			DESCRIPTION
        				"
        					流量统计的时间
        				"
                    ::= { rcftRemoteMoudleE1StatisticEntry 7 }


       --------------------------E1端口的告警--------------------------

       rcftRemoteMoudleE1LOSTrap	NOTIFICATION-TYPE
      	OBJECTS{
			rcftRemoteMoudleE1AlarmStatus
      	}
      	STATUS current
     	DESCRIPTION
     	"
     		局端设备上E1接口的LOS告警
     	"
     	::= { rcftRemoteMoudleE1Traps 1 }

       rcftRemoteMoudleE1AISTrap	NOTIFICATION-TYPE
      	OBJECTS{
			rcftRemoteMoudleE1AlarmStatus
      	}
      	STATUS current
     	DESCRIPTION
     	"
     		局端设备上E1接口的AIS告警
     	"
     	::= { rcftRemoteMoudleE1Traps 2 }

       rcftRemoteMoudleE1CRCTrap	NOTIFICATION-TYPE
      	OBJECTS{
			rcftRemoteMoudleE1AlarmStatus
      	}
      	STATUS current
     	DESCRIPTION
     	"
     		局端设备上E1接口的CRC告警
     	"
     	::= { rcftRemoteMoudleE1Traps 3 }

       rcftRemoteMoudleE1CVTrap	NOTIFICATION-TYPE
      	OBJECTS{
			rcftRemoteMoudleE1AlarmStatus
      	}
      	STATUS current
     	DESCRIPTION
     	"
     		局端设备上E1接口的CV告警
     	"
     	::= { rcftRemoteMoudleE1Traps 4 }

       rcftRemoteMoudleE1LOFTrap	NOTIFICATION-TYPE
      	OBJECTS{
			rcftRemoteMoudleE1AlarmStatus
      	}
      	STATUS current
     	DESCRIPTION
     	"
     		局端设备上E1接口的LOF告警
     	"
     	::= { rcftRemoteMoudleE1Traps 5 }

       rcftRemoteMoudleE1ErrorCodeTrap	NOTIFICATION-TYPE
      	OBJECTS{
			rcftRemoteMoudleE1Status
      	}
      	STATUS current
     	DESCRIPTION
     	"
     		局端设备上E1接口的误码测试告警
     	"
     	::= { rcftRemoteMoudleE1Traps 6 }

   --------------------------V35端口的对象---------------------------------

    rcftRemoteMoudleV35Table OBJECT-TYPE
       SYNTAX  SEQUENCE OF RcftRemoteMoudleV35Entry
       MAX-ACCESS  not-accessible
       STATUS  current
       DESCRIPTION
       "
         The V35 PORT table.
       "
       ::= { rcftRemoteMoudleV35Objects 1 }

    rcftRemoteMoudleV35Entry OBJECT-TYPE
       SYNTAX  RcftRemoteMoudleV35Entry
       MAX-ACCESS  not-accessible
       STATUS  current
       DESCRIPTION
       "
          An entry in the V35 PORT table.

       "
       INDEX   { rcftChassisIndex, rcftSlotIndex,
       			 rcftRemoteDeviceIndex, rcftRemoteMoudleIndex,
       			 rcftRemoteMoudleV35Index }
       ::= { rcftRemoteMoudleV35Table 1 }


    RcftRemoteMoudleV35Entry ::=
       SEQUENCE {
       rcftRemoteMoudleV35Index		 	Integer32,
       rcftRemoteMoudleV35AlarmStatus	INTEGER,
       rcftRemoteMoudleV35Status		INTEGER
       }

    rcftRemoteMoudleV35Index OBJECT-TYPE
    	SYNTAX	   Integer32
    	MAX-ACCESS read-only
    	STATUS		current
    	DESCRIPTION
    	"
    		V35口的索引
    	"
        ::= { rcftRemoteMoudleV35Entry 1 }

    rcftRemoteMoudleV35AlarmStatus	OBJECT-TYPE
    	SYNTAX	INTEGER
    	MAX-ACCESS read-only
    	STATUS		current
    	DESCRIPTION
    	"
			其它位	保留	固定000'b。
			BIT11	RAIS    站在本地设备上看对端V35口所占那一路E1的AIS告警 1：正常 	0：告警
			BIT10	RCV     站在本地设备上看对端V35口所占那一路E1的CV告警  1：正常 	0：告警
			BIT9	RLOF	站在本地设备上看对端V35口所占那一路E1的LOF告警 1：正常 	0：告警
			BIT8	AIS     V35口所占那一路E1的AIS告警 1：正常 	0：告警
			BIT7	CV      V35口所占那一路E1的CV告警  1：正常 	0：告警
			BIT6	LOF	    V35口所占那一路E1的LOF告警 1：正常 	0：告警
			BIT5	PATT		1：误码测试正常       0：误码测试告警
			BIT4    CRC_ALARM   1：正常 			  0：告警

			BIT3	DCD_O		1：DCD信号UP；        0：DCD信号DOWN。
			BIT2	CTS_O		1：CTS信号UP；        0：CTS信号DOWN。
			BIT1	DTR_I		1：DTR信号UP；        0：DTR信号DOWN。
			BIT0	RTS_I		1：RTS信号UP；        0：RTS信号DOWN。
    	"
        ::= { rcftRemoteMoudleV35Entry 2 }

 	rcftRemoteMoudleV35Status     OBJECT-TYPE
 		SYNTAX	INTEGER
    	MAX-ACCESS read-write
    	STATUS		current
    	DESCRIPTION
    	"
    		BIT15   DSR_O 		0：DSR信号up     1：DSR信号down
			BIT14   DTR_I 		0：DTR信号up     1：DTR信号down
			BIT13   RTS_I	 	0：RTS信号up     1：RTS信号down
			BIT12	故障转移功能（E1到V35） 	0:禁止     1：使能
			BIT11   CTS_O 		0：CTS信号up    1：CTS信号down
			BIT10   DCD_O 		0：DCD信号up    1：DCD信号down
			BIT9	RD状态		0：禁止 1：使能
			BIT8	TD状态		0：禁止 1：使能

			BIT7~6  时钟方式		   11：主时钟  00：从时钟
									   01：V35终端时钟  10：V35终端时钟且带宽跟随
			BIT5    时隙带宽控制	   0：从控； 1：主控
 			BIT4    ALOOP功能          0：禁止； 1：使能
 			BIT3    DLOOP功能  		   0：禁止； 1：使能
			BIT2    RLOOP功能          0：禁止； 1：使能
			BIT1    远端环回状态       0：未成功； 1：成功
			BIT0    RX_CLK		       0：正相； 1：反相
    	"
        ::= { rcftRemoteMoudleV35Entry 3 }

    --------------------------V35端口的告警--------------------------


	  rcftRemoteAudioPortTable OBJECT-TYPE
       SYNTAX  SEQUENCE OF RcftRemoteAudioPortEntry
       MAX-ACCESS  not-accessible
       STATUS  current
       DESCRIPTION
       "
         The Audio PORT table.
       "
       ::= { rcftRemoteAudioPortObjects 1 }

    rcftRemoteAudioPortEntry OBJECT-TYPE
       SYNTAX  RcftRemoteAudioPortEntry
       MAX-ACCESS  not-accessible
       STATUS  current
       DESCRIPTION
       "
          An entry in the Audio PORT table.

       "
       INDEX   { rcftChassisIndex, rcftSlotIndex,
        			rcftRemoteDeviceIndex,rcftRemoteAudioPortIndex }
       ::= { rcftRemoteAudioPortTable 1 }


    RcftRemoteAudioPortEntry ::=
       SEQUENCE {
       rcftRemoteAudioPortIndex		 	Integer32,
       rcftRemoteAudioPortStatus			INTEGER,
       rcftRemoteAudioPortPosition		INTEGER,
       rcftRemoteAudioPortType		INTEGER
       }

    rcftRemoteAudioPortIndex OBJECT-TYPE
    	SYNTAX	 Integer32
    	MAX-ACCESS read-only
    	STATUS	current
    	DESCRIPTION
    	"
    		Audio口的索引
    	"
        ::= { rcftRemoteAudioPortEntry 1 }

    rcftRemoteAudioPortStatus OBJECT-TYPE
    	SYNTAX	INTEGER
    	MAX-ACCESS read-write
    	STATUS	current
    	DESCRIPTION
    	"
			BIT1    LOS   音频口有无信号告警   	1：正常    	0：告警
			BIT0	音频口的开关状态	        0：关闭		1：打开
    	"
        ::= { rcftRemoteAudioPortEntry 2 }

      rcftRemoteAudioPortPosition OBJECT-TYPE
    	SYNTAX INTEGER
    	MAX-ACCESS read-only
    	STATUS current
    	DESCRIPTION
    	"
    		音频口的位置信息：
    		bit7-4：盘
    		bit3-0：槽
    	"
    	::={ rcftRemoteAudioPortEntry 3}


      rcftRemoteAudioPortType OBJECT-TYPE
    	SYNTAX	INTEGER
    	MAX-ACCESS read-only
    	STATUS	current
    	DESCRIPTION
    	"
			音频口的类型：
			1：电话用户端
			2：电话中继端
			3：高保真双向音频
			4：高保真音频编码
			5：高保真音频解码
    	"
        ::= { rcftRemoteAudioPortEntry 4 }



      rcftRemoteVideoPortTable OBJECT-TYPE
       SYNTAX  SEQUENCE OF RcftRemoteVideoPortEntry
       MAX-ACCESS  not-accessible
       STATUS  current
       DESCRIPTION
       "
         The Video PORT table.
       "
       ::= { rcftRemoteVideoPortObjects 1 }

    rcftRemoteVideoPortEntry OBJECT-TYPE
       SYNTAX  RcftRemoteVideoPortEntry
       MAX-ACCESS  not-accessible
       STATUS  current
       DESCRIPTION
       "
          An entry in the Video PORT table.

       "
       INDEX   { rcftChassisIndex, rcftSlotIndex,
        			rcftRemoteDeviceIndex,rcftRemoteVideoPortIndex }
       ::= { rcftRemoteVideoPortTable 1 }


    RcftRemoteVideoPortEntry ::=
       SEQUENCE {
       rcftRemoteVideoPortIndex		 	Integer32,
       rcftRemoteVideoPortStatus			INTEGER,
       rcftRemoteVideoPortPosition		INTEGER,
       rcftRemoteVideoPortSourceID		INTEGER
       }

    rcftRemoteVideoPortIndex OBJECT-TYPE
    	SYNTAX	   Integer32
    	MAX-ACCESS read-only
    	STATUS		current
    	DESCRIPTION
    	"
    		Video口的索引
    	"
        ::= { rcftRemoteVideoPortEntry 1 }

    rcftRemoteVideoPortStatus	OBJECT-TYPE
    	SYNTAX	INTEGER
    	MAX-ACCESS read-write
    	STATUS		current
    	DESCRIPTION
    	"
			BIT7	视频口输入信号状态			0：无信号；	1：有信号
			BIT6	视频口输出信号状态			0：无信号；	1：有信号
			BIT5	视频口输入信号开关			0：关闭；	1：打开
			BIT4	视频口输出信号开关			0：关闭；	1：打开
			BIT3	视频口方向					0：单向；	1：双向
			BIT2	视频口的开关状态			0：关闭		1：打开
			BIT1	视频口的属性				0：输入， 	1：输出
			BIT0    LOS   视频口有无信号告警	0：正常    	1：告警
    	"
        ::= { rcftRemoteVideoPortEntry 2 }

      rcftRemoteVideoPortPosition OBJECT-TYPE
    	SYNTAX INTEGER
    	MAX-ACCESS read-only
    	STATUS current
    	DESCRIPTION
    	"
    		视频口的位置信息：
    		bit7-4：盘
    		bit3-0：槽
    	"
    	::={ rcftRemoteVideoPortEntry 3}


      rcftRemoteVideoPortSourceID OBJECT-TYPE
    	SYNTAX	INTEGER
    	MAX-ACCESS read-write
    	STATUS		current
    	DESCRIPTION
    	"
			视频源ID
    	"
        ::= { rcftRemoteVideoPortEntry 4 }

     --------------------------Video 视频口的告警------------------------

       rcftRemoteVideoPortSignalLos  NOTIFICATION-TYPE
      	OBJECTS{
			rcftRemoteVideoPortStatus
      	}
      	STATUS current
     	DESCRIPTION
     	"
     		局端设备上Video 视频口有无信号告警
     	"
     	::= { rcftRemoteVideoPortTraps 1 }


     	rcftRemoteVideoPortSignalInLos  NOTIFICATION-TYPE
      	OBJECTS{
			rcftRemoteVideoPortStatus
      	}
      	STATUS current
     	DESCRIPTION
     	"
     		局端设备上Video 视频口输入有无信号告警
     	"
     	::= { rcftRemoteVideoPortTraps 2 }



     	rcftRemoteVideoPortSignalOutLos  NOTIFICATION-TYPE
      	OBJECTS{
			rcftRemoteVideoPortStatus
      	}
      	STATUS current
     	DESCRIPTION
     	"
     		局端设备上Video 视频口输出有无信号告警
     	"
     	::= { rcftRemoteVideoPortTraps 3 }




   ---------------------------DataPort-----------------------------
    rcftRemoteDataPortTable OBJECT-TYPE
       SYNTAX  SEQUENCE OF RcftRemoteDataPortEntry
       MAX-ACCESS  not-accessible
       STATUS  current
       DESCRIPTION
       "
         The Data PORT table.
       "
       ::= { rcftRemoteDataPortObjects 1 }

    rcftRemoteDataPortEntry OBJECT-TYPE
       SYNTAX  RcftRemoteDataPortEntry
       MAX-ACCESS  not-accessible
       STATUS  current
       DESCRIPTION
       "
          An entry in the Data PORT table.

       "
       INDEX   { rcftChassisIndex, rcftSlotIndex,
        			rcftRemoteDeviceIndex,rcftRemoteDataPortIndex }
       ::= { rcftRemoteDataPortTable 1 }


    RcftRemoteDataPortEntry ::=
       SEQUENCE {
       rcftRemoteDataPortIndex		 	Integer32,
       rcftRemoteDataPortStatus			INTEGER,
       rcftRemoteDataPortPosition		INTEGER,
       rcftRemoteDataPortType		INTEGER
       }

    rcftRemoteDataPortIndex OBJECT-TYPE
    	SYNTAX	   Integer32
    	MAX-ACCESS read-only
    	STATUS		current
    	DESCRIPTION
    	"
    		Data 口的索引
    	"
        ::= { rcftRemoteDataPortEntry 1 }

    rcftRemoteDataPortStatus	OBJECT-TYPE
    	SYNTAX	INTEGER
    	MAX-ACCESS read-write
    	STATUS		current
    	DESCRIPTION
    	"
			BIT1    数据口有无信号			   	1：正常    	0：告警
			BIT0	数据口的开关状态	        0：关闭		1：打开
    	"
        ::= { rcftRemoteDataPortEntry 2 }

    	rcftRemoteDataPortPosition OBJECT-TYPE
    	SYNTAX INTEGER
    	MAX-ACCESS read-only
    	STATUS current
    	DESCRIPTION
    	"
    		数据口的位置信息：
    		bit7-4：盘
    		bit3-0：槽
    	"
    	::={ rcftRemoteDataPortEntry 3}

       rcftRemoteDataPortType OBJECT-TYPE
    	SYNTAX	INTEGER
    	MAX-ACCESS read-only
    	STATUS		current
    	DESCRIPTION
    	"
			数据口类型：
			1：232
			2：422
			3：485
			4：开关量
    	"
        ::= { rcftRemoteDataPortEntry 4 }




    rcftRemoteSimpleModuleTable OBJECT-TYPE
       SYNTAX  SEQUENCE OF RcftRemoteSimpleModuleEntry
       MAX-ACCESS  not-accessible
       STATUS  current
       DESCRIPTION
       "
         The Data PORT table.
       "
       ::= { rcftRemoteSimpleModuleObjects 1 }

    rcftRemoteSimpleModuleEntry OBJECT-TYPE
       SYNTAX  RcftRemoteSimpleModuleEntry
       MAX-ACCESS  not-accessible
       STATUS  current
       DESCRIPTION
       "
          An entry in the SimpleModule table.

       "
       INDEX   { rcftChassisIndex, rcftSlotIndex,
        			rcftRemoteDeviceIndex,rcftRemoteSimpleModuleIndex }
       ::= { rcftRemoteSimpleModuleTable 1 }


    RcftRemoteSimpleModuleEntry ::=
       SEQUENCE {
       rcftRemoteSimpleModuleIndex		 	Integer32,
       rcftRemoteSimpleModuleExist			INTEGER,
       rcftRemoteSimpleModulePosition		INTEGER,
       rcftRemoteSimpleModuleStatus 	INTEGER,
       rcftRemoteSimpleModuleType		INTEGER
       }

    rcftRemoteSimpleModuleIndex OBJECT-TYPE
    	SYNTAX	   Integer32
    	MAX-ACCESS read-only
    	STATUS		current
    	DESCRIPTION
    	"
    		SimpleModule 口的索引
    	"
        ::= { rcftRemoteSimpleModuleEntry 1 }

        rcftRemoteSimpleModuleExist OBJECT-TYPE
        SYNTAX INTEGER
        MAX-ACCESS read-only
        STATUS current
        DESCRIPTION
        "
        	simplemodule 小模块是否在位，1：在位，2：不在位
        "
        ::= {rcftRemoteSimpleModuleEntry 2}

    	rcftRemoteSimpleModulePosition OBJECT-TYPE
    	SYNTAX INTEGER
    	MAX-ACCESS read-only
    	STATUS current
    	DESCRIPTION
    	"
    		SimpleModule的位置信息：
    		bit7-4：盘
    		bit3-0：槽
    	"
    	::={ rcftRemoteSimpleModuleEntry 3}

    	rcftRemoteSimpleModuleStatus   OBJECT-TYPE
    	SYNTAX INTEGER
    	MAX-ACCESS read-write
    	STATUS current
    	DESCRIPTION
    	"
    		Bit1：小模块智能非智能标志，0：非智能， 1：智能
    	"
    	::={ rcftRemoteSimpleModuleEntry 4}


       rcftRemoteSimpleModuleType OBJECT-TYPE
    	SYNTAX	INTEGER
    	MAX-ACCESS read-only
    	STATUS		current
    	DESCRIPTION
    	"
			SimpleModule类型：

			对于非智能小模块：
			1   一路232
			2   两路232
			3   一路422
			4   一路485
			5   两路485
			6   以太网模块
			7   开关量
			8   电话用户端
			9   电话中继端
			10   两路高保真双向音频
			11   两路高保真音频编码
			12   两路高保真音频解码

			智能小模块：1000+x，为对应的非智能小模块类型。

    	"
        ::= { rcftRemoteSimpleModuleEntry 5 }






    rcftRemoteVLANTable OBJECT-TYPE
       SYNTAX  SEQUENCE OF RcftRemoteVLANEntry
       MAX-ACCESS  not-accessible
       STATUS  current
       DESCRIPTION
       "
         The VLAN table.
       "
       ::= { rcftRemoteVLANObjects 1 }

    rcftRemoteVLANEntry OBJECT-TYPE
       SYNTAX  RcftRemoteVLANEntry
       MAX-ACCESS  not-accessible
       STATUS  current
       DESCRIPTION
       "
          An entry in the VLAN table.

       "
       INDEX   { rcftChassisIndex, rcftSlotIndex,
        			rcftRemoteDeviceIndex,rcftRemoteVLANIndex }
       ::= { rcftRemoteVLANTable 1 }


    RcftRemoteVLANEntry ::=
       SEQUENCE {
       rcftRemoteVLANIndex		Integer32,
       rcftRemoteVLANStatus		INTEGER,
       rcftRemoteVLANmember		INTEGER,
       rcftRemoteVID 			INTEGER
       }

    rcftRemoteVLANIndex OBJECT-TYPE
    	SYNTAX	   Integer32
    	MAX-ACCESS read-only
    	STATUS		current
    	DESCRIPTION
    	"
    		VLAN 表项 的索引
    	"
        ::= { rcftRemoteVLANEntry 1 }

     rcftRemoteVLANStatus  OBJECT-TYPE
    	SYNTAX	   INTEGER
    	MAX-ACCESS read-write
    	STATUS		current
    	DESCRIPTION
    	"
    		VLAN 表项 状态
    		1：激活
    		2：挂起

    	"
        ::= { rcftRemoteVLANEntry 2 }

     rcftRemoteVLANmember  OBJECT-TYPE
    	SYNTAX	   INTEGER
    	MAX-ACCESS read-write
    	STATUS		current
    	DESCRIPTION
    	"
    		VLAN表项的端口列表。
			bit31~0对应第32路~~第1路EthFe口，第n位为1表示第n+1端口为该VLAN成员。
    		例如：bit3=1，bit0=1，表示端口4和端口1为该VLAN的成员。
    	"
        ::= { rcftRemoteVLANEntry 3 }

      rcftRemoteVID  OBJECT-TYPE
    	SYNTAX	   INTEGER
    	MAX-ACCESS read-write
    	STATUS		current
    	DESCRIPTION
    	"
    		VLANID，范围1~4094。
    	"
        ::= { rcftRemoteVLANEntry 4 }



        ---------------------- FPGA 流量统计 ----------------------
    rcftRemoteStatisticTable OBJECT-TYPE
	        SYNTAX SEQUENCE OF RcftRemoteStatisticEntry
	        MAX-ACCESS not-accessible
	        STATUS current
	        DESCRIPTION
	          "
	          局端设备 FPGA 侧的流量统计表.
	          "
            ::= {rcftRemoteStatisticPerformance 1}
	    rcftRemoteStatisticEntry OBJECT-TYPE
	        SYNTAX RcftRemoteStatisticEntry
	        MAX-ACCESS not-accessible
	        STATUS current
	        DESCRIPTION
	          "
	             以rcftSlotFPGAVCGIndex为索引
	          "
	        INDEX   { rcftChassisIndex, rcftSlotIndex, rcftRemoteDeviceIndex, rcftRemotePortIndex }
       		::= { rcftRemoteStatisticTable 1 }

	    RcftRemoteStatisticEntry ::= SEQUENCE {
	    		rcftRemotePortIndex			Integer32,
	    		rcftRemotePortType			INTEGER,
				rcftRemoteRxPackets    		Counter32,
				rcftRemoteRxLosPackets        Counter32,
				rcftRemoteRxPreabErrPackets   Counter32,
				rcftRemoteRxFCSErrPackets     Counter32,
				rcftRemoteRxUnderSizePackets      Counter32,
				rcftRemoteRxOverSizePackets        Counter32,
				rcftRemoteRxPausePackets      Counter32,
				rcftRemoteRxOamPackets        Counter32,
				rcftRemoteRxBytes             Counter32,
				rcftRemoteTxPackets           Counter32,
				rcftRemoteTxFCSErrPackets     Counter32,
				rcftRemoteTxPausePackets      Counter32,
				rcftRemoteTxOamPackets        Counter32,
				rcftRemoteTxBytes             Counter32,
				rcftRemoteFluxTimer			Counter32

				}

		rcftRemotePortIndex   OBJECT-TYPE
    		SYNTAX	   Integer32
    		MAX-ACCESS read-only
    		STATUS		current
    		DESCRIPTION
    		"
    			索引
    		"
        	::= { rcftRemoteStatisticEntry 1 }

        rcftRemotePortType   OBJECT-TYPE
    		SYNTAX	   INTEGER
    		MAX-ACCESS read-only
    		STATUS		current
    		DESCRIPTION
    		"
    			接口类型

    			1：ethfe口
    			2：ethfx口
    			3：e1口

    		"
        	::= { rcftRemoteStatisticEntry 2 }

		rcftRemoteRxPackets    OBJECT-TYPE
			SYNTAX Counter32
			MAX-ACCESS read-only
			STATUS current
			DESCRIPTION
			"
				接收包数
			"
			::= { rcftRemoteStatisticEntry 3 }

		rcftRemoteRxLosPackets        OBJECT-TYPE
			SYNTAX Counter32
			MAX-ACCESS read-only
			STATUS current
			DESCRIPTION
			"
				接收丢包数
			"
			::= { rcftRemoteStatisticEntry 4 }

		rcftRemoteRxPreabErrPackets   OBJECT-TYPE
			SYNTAX Counter32
			MAX-ACCESS read-only
			STATUS current
			DESCRIPTION
			"
				接收前导码错误包数
			"
			::= { rcftRemoteStatisticEntry 5 }

		rcftRemoteRxFCSErrPackets     OBJECT-TYPE
			SYNTAX Counter32
			MAX-ACCESS read-only
			STATUS current
			DESCRIPTION
			"
				接收FCS错误包数
			"
			::= { rcftRemoteStatisticEntry 6 }

		rcftRemoteRxUnderSizePackets      OBJECT-TYPE
			SYNTAX Counter32
			MAX-ACCESS read-only
			STATUS current
			DESCRIPTION
			"
				接收超短包数
			"
			::= { rcftRemoteStatisticEntry 7 }

		rcftRemoteRxOverSizePackets        OBJECT-TYPE
			SYNTAX Counter32
			MAX-ACCESS read-only
			STATUS current
			DESCRIPTION
			"
				接收超长报数
			"
			::= { rcftRemoteStatisticEntry 8 }

		rcftRemoteRxPausePackets      OBJECT-TYPE
			SYNTAX Counter32
			MAX-ACCESS read-only
			STATUS current
			DESCRIPTION
			"
				接收PAUSE 包数
			"
			::= { rcftRemoteStatisticEntry 9 }

		rcftRemoteRxOamPackets        OBJECT-TYPE
			SYNTAX Counter32
			MAX-ACCESS read-only
			STATUS current
			DESCRIPTION
			"
				接收OAM包数
			"
			::= { rcftRemoteStatisticEntry 10 }

		rcftRemoteRxBytes             OBJECT-TYPE
			SYNTAX Counter32
			MAX-ACCESS read-only
			STATUS current
			DESCRIPTION
			"
				接收字节数
			"
			::= { rcftRemoteStatisticEntry 11 }

		rcftRemoteTxPackets           OBJECT-TYPE
			SYNTAX Counter32
			MAX-ACCESS read-only
			STATUS current
			DESCRIPTION
			"
				发送包数
			"
			::= { rcftRemoteStatisticEntry 12 }

		rcftRemoteTxFCSErrPackets     OBJECT-TYPE
			SYNTAX Counter32
			MAX-ACCESS read-only
			STATUS current
			DESCRIPTION
			"
				发送FCS错误包数（由GFP解帧模块检测到的）
			"
			::= { rcftRemoteStatisticEntry 13 }

		rcftRemoteTxPausePackets      OBJECT-TYPE
			SYNTAX Counter32
			MAX-ACCESS read-only
			STATUS current
			DESCRIPTION
			"
				发送PAUSE包数
			"
			::= { rcftRemoteStatisticEntry 14 }

		rcftRemoteTxOamPackets        OBJECT-TYPE
			SYNTAX Counter32
			MAX-ACCESS read-only
			STATUS current
			DESCRIPTION
			"
				发送OAM包数
			"
			::= { rcftRemoteStatisticEntry 15 }

		rcftRemoteTxBytes      OBJECT-TYPE
			SYNTAX Counter32
			MAX-ACCESS read-only
			STATUS current
			DESCRIPTION
			"
				发送字节数
			"
			::= { rcftRemoteStatisticEntry 16 }

		rcftRemoteFluxTimer    OBJECT-TYPE
			SYNTAX Counter32
			MAX-ACCESS read-only
			STATUS current
			DESCRIPTION
			"
				流量统计时间
			"
			::= { rcftRemoteStatisticEntry 17 }



   rcftRemoteVCGTable OBJECT-TYPE
       SYNTAX  SEQUENCE OF RcftRemoteVCGEntry
       MAX-ACCESS  not-accessible
       STATUS  current
       DESCRIPTION
       "
         The VCG table.
       "
       ::= { rcftRemoteVCGObjects 1 }

    rcftRemoteVCGEntry OBJECT-TYPE
       SYNTAX  RcftRemoteVCGEntry
       MAX-ACCESS  not-accessible
       STATUS  current
       DESCRIPTION
       "
          An entry in the VCG table.

       "
       INDEX   { rcftChassisIndex, rcftSlotIndex, rcftRemoteDeviceIndex, rcftRemoteVCGIndex }
       ::= { rcftRemoteVCGTable 1 }


    RcftRemoteVCGEntry ::=
       SEQUENCE {
       rcftRemoteVCGIndex		 	Integer32,
       rcftRemoteVCGStatus		INTEGER,
       rcftRemoteVCGLoopStatus	INTEGER,
       rcftRemoteVCGLcasXPR		INTEGER,
       rcftRemoteVCGLcasXAR		INTEGER,
       rcftRemoteVCGLcasXPT		INTEGER,
       rcftRemoteVCGLcasXAT		INTEGER,
       rcftRemoteVCGAlarmStatus	INTEGER,
       rcftRemoteVCGRxISPTPID		INTEGER,
       rcftRemoteVCGTxISPTPID		INTEGER,
       rcftRemoteVCGBaseCoS 		INTEGER,
       rcftRemoteVCGVLANID		INTEGER,
       rcftRemoteVCGMemberList	OCTET STRING,
       rcftRemoteVCGMemberStatus    OCTET STRING,
       rcftRemoteVCGMemberRxCode    OCTET STRING,
       rcftRemoteVCGMemberTxCode    OCTET STRING,
       rcftRemoteVCGMemberAlarmStatus  	OCTET STRING,
       rcftRemoteToLVCGMemberAlarmStatus  OCTET STRING,
       rcftRemoteToLVCGMemberAlarmStatus	OCTET STRING


       }


    rcftRemoteVCGIndex OBJECT-TYPE
    	SYNTAX	   Integer32
    	MAX-ACCESS read-only
    	STATUS		current
    	DESCRIPTION
    	"
    		VCG 的索引
    	"
        ::= { rcftRemoteVCGEntry 1 }

        rcftRemoteVCGStatus OBJECT-TYPE
        SYNTAX INTEGER
        MAX-ACCESS read-write
        STATUS current
        DESCRIPTION
        "
        	bit10:CSF发送				1：使能，0：禁止
        	bit6：是否带tag 				1：使能，0：禁止
        	bit5：CheckLoop。				1：使能，0：禁止
        	bit4：Fcs。						1：使能，0：禁止
        	bit3：GFP净荷扰码Scrb。			1：使能，0：禁止
        	bit2：VLI。						1：使能，0：禁止
        	bit1：Vcat。					1：使能，0：禁止
        	bit0：Lcas。					1：使能，0：禁止

        	LCAS on时，VCAT不可配（内部强制使能）。
        	只有LCAS off时，网管可配VCAT。
			VLI始终可配，但是只在LCAS off、VCAT 禁止时配置生效。
        "
        ::= {rcftRemoteVCGEntry 2}

        rcftRemoteVCGLoopStatus	OBJECT-TYPE
        SYNTAX INTEGER
        MAX-ACCESS read-only
        STATUS current
        DESCRIPTION
        "
           0：无环，1~63：表示有环的VCG号
        "
        ::= {rcftRemoteVCGEntry 3}
        rcftRemoteVCGLcasXPR  OBJECT-TYPE
        SYNTAX INTEGER
        MAX-ACCESS read-only
        STATUS current
        DESCRIPTION
        "
           	接收配置成员数（1-E1接口数目）
        "
        ::= {rcftRemoteVCGEntry 4}

        rcftRemoteVCGLcasXAR  OBJECT-TYPE
        SYNTAX INTEGER
        MAX-ACCESS read-only
        STATUS current
        DESCRIPTION
        "
           	接收实际成员数（1-E1接口数目）
        "
        ::= {rcftRemoteVCGEntry 5}

        rcftRemoteVCGLcasXPT  OBJECT-TYPE
        SYNTAX INTEGER
        MAX-ACCESS read-only
        STATUS current
        DESCRIPTION
        "
           	 发送配置成员数（1-E1接口数目）
        "
        ::= {rcftRemoteVCGEntry 6}

        rcftRemoteVCGLcasXAT  OBJECT-TYPE
        SYNTAX INTEGER
        MAX-ACCESS read-only
        STATUS current
        DESCRIPTION
        "
           	 发送实际成员数（1-E1接口数目）
        "
        ::= {rcftRemoteVCGEntry 7}
        rcftRemoteVCGAlarmStatus	OBJECT-TYPE
        SYNTAX INTEGER
        MAX-ACCESS read-only
        STATUS current
        DESCRIPTION
        "
           	 VCG 告警
           	 bit0：GID
           	 bit1：LOA
			 bit2：LFD
			 bit3：CFS

           	 LCAS ON时的告警
             bit4：TLCT
           	 bit5：PLCT
           	 bit6：TLCR
			 bit7：PLCR

			 bit8：对端GID：
			 bit9：对端LOA
			 bit10：对端LFD

        "
        ::= {rcftRemoteVCGEntry 8}

       rcftRemoteVCGRxISPTPID	OBJECT-TYPE
        SYNTAX INTEGER
        MAX-ACCESS read-write
        STATUS current
        DESCRIPTION
       	"
           	发送侧 TPID
       	"
       	::= {rcftRemoteVCGEntry 9}

       rcftRemoteVCGTxISPTPID	OBJECT-TYPE
        SYNTAX INTEGER
        MAX-ACCESS read-write
        STATUS current
        DESCRIPTION
       	"
           	接收侧 TPID
       	"
       	::= {rcftRemoteVCGEntry 10}


       rcftRemoteVCGBaseCoS 		OBJECT-TYPE
        SYNTAX INTEGER
        MAX-ACCESS read-write
        STATUS current
        DESCRIPTION
       	"
           	COS：0~7
       	"
       	::= {rcftRemoteVCGEntry 11}

       rcftRemoteVCGVLANID  OBJECT-TYPE
        SYNTAX INTEGER
        MAX-ACCESS read-write
        STATUS current
        DESCRIPTION
       	"
           	VLANID
       	"
       	::= {rcftRemoteVCGEntry 12}

       	rcftRemoteVCGMemberList  	OBJECT-TYPE
	  	SYNTAX	OCTET STRING(SIZE (0..15))
		MAX-ACCESS	read-write
		STATUS	current
		DESCRIPTION
    	"
    		E1成员列表，每个字节表示1个成员对应的E1端口号。
			此节点为字节串，各成员之间有先后顺序，字节串从左到右依次表示1-N个成员。
			每个字节为0表示该成员无效。

    	"
        ::= { rcftRemoteVCGEntry 13 }


       	rcftRemoteVCGMemberStatus		OBJECT-TYPE
	  	SYNTAX	OCTET STRING(SIZE (0..15))
		MAX-ACCESS	read-write
		STATUS	current
		DESCRIPTION
    	"
    		此节点为字节串，各成员之间有先后顺序，字节串从左到右依次表示1-N个成员。
			每个字节的：
    		bit0：成员的接收RX状态。1：OK， 0：Error。
			bit1：成员的发送TX状态。1：OK， 0：Error。
    	"
        ::= { rcftRemoteVCGEntry 14 }

       rcftRemoteVCGMemberRxCode		OBJECT-TYPE
	  	SYNTAX	OCTET STRING(SIZE (0..15))
		MAX-ACCESS	read-only
		STATUS	current
		DESCRIPTION
    	"
    		此节点为字节串，各成员之间有先后顺序，字节串从左到右依次表示1-N个成员。
			每个字节的枚举值如下：

    		VCG成员接收控制字：
    		1：FIXED  。固定带宽，不支持LCAS
    		2：ADD    。当前成员添加到VCG组中
    		3：NORM   。正常传送，当前成员已配置到VCG组中，且通道良好。
    		4：EOS    。该组中的最后一个成员
    		5：IDLE   。该成员没有配置到VCG组中
    		6：DNU	  。该成员是VCG成员，但是通道故障。
      	"
        ::= { rcftRemoteVCGEntry 15 }

       rcftRemoteVCGMemberTxCode		OBJECT-TYPE
	  	SYNTAX	OCTET STRING(SIZE (0..15))
		MAX-ACCESS	read-only
		STATUS	current
		DESCRIPTION
    	"
    		此节点为字节串，各成员之间有先后顺序，字节串从左到右依次表示1-N个成员。
			每个字节的枚举值如下：

    		VCG成员发送控制字：
    		1：FIXED  。固定带宽，不支持LCAS
    		2：ADD    。当前成员添加到VCG组中
    		3：NORM   。正常传送，当前成员已配置到VCG组中，且通道良好。
    		4：EOS    。该组中的最后一个成员
    		5：IDLE   。该成员没有配置到VCG组中
    		6：DNU	  。该成员是VCG成员，但是通道故障。
       	"
        ::= { rcftRemoteVCGEntry 16 }

       rcftRemoteVCGMemberAlarmStatus	OBJECT-TYPE
	  	SYNTAX	OCTET STRING(SIZE (0..15))
		MAX-ACCESS	read-only
		STATUS	current
		DESCRIPTION
    	"
    		成员告警状态，此节点为字节串，各成员之间有先后顺序，字节串从左到右依次表示1-N个成员。
			每个字节的bit位定义如下：

    		VCG 成员的告警
    		bit3：   LOA （与MND合并了）
    		bit2：   SQM
    		bit1：   CRC
    		bit0：   LOM
    	"
        ::= { rcftRemoteVCGEntry 17 }

      rcftRemoteToLVCGMemberAlarmStatus   OBJECT-TYPE
	  	SYNTAX	OCTET STRING(SIZE (0..15))
		MAX-ACCESS	read-only
		STATUS	current
		DESCRIPTION
    	"
    		对端VCG 成员告警状态，此节点为字节串，各成员之间有先后顺序，字节串从左到右依次表示1-N个成员。
			每个字节的bit位定义如下：

    		bit3：   LOA （与MND合并了）
    		bit2：   SQM
    		bit1：   CRC
    		bit0：   LOM
    	"
        ::= { rcftRemoteVCGEntry 18 }


         --------------------------VCG GFP帧流量统计--------------------------
         rcftRemoteVCGStatisticTable OBJECT-TYPE
	        SYNTAX SEQUENCE OF RcftRemoteVCGStatisticEntry
	        MAX-ACCESS not-accessible
	        STATUS current
	        DESCRIPTION
	          "
	          局端设备GFP的统计表.
	          "
            ::= {rcftRemoteVCGPerformance 1}
	    rcftRemoteVCGStatisticEntry OBJECT-TYPE
	        SYNTAX RcftRemoteVCGStatisticEntry
	        MAX-ACCESS not-accessible
	        STATUS current
	        DESCRIPTION
	          "
	             以rcftRemoteVCGIndex为索引
	          "
	        AUGMENTS { rcftRemoteVCGEntry }
	        ::= {rcftRemoteVCGStatisticTable 1}

	    RcftRemoteVCGStatisticEntry ::= SEQUENCE {
				rcftRemoteVCGRxClientPackets    	  Counter32,
				rcftRemoteVCGRxIdlePackets          Counter32,
				rcftRemoteVCGRxMgmntPackets		  	  Counter32,
				rcftRemoteVCGRxFCSErrMgmntPackets     Counter32,
				rcftRemoteVCGRxLenErrPackets   	  Counter32,
				rcftRemoteVCGRxFCSErrClientPackets    Counter32,
				rcftRemoteVCGRxThecErrPackets     Counter32,
				rcftRemoteVCGRxEhecErrPackets     Counter32,
				rcftRemoteVCGRxCIDErrPackets      Counter32,
				rcftRemoteVCGRxSpareErrPackets    Counter32,
				rcftRemoteVCGRxChecCorPackets     Counter32,
				rcftRemoteVCGRxThecCorPackets     Counter32,
				rcftRemoteVCGRxEhecCorPackets     Counter32,
				rcftRemoteVCGRxBytes          	  Counter32,
				rcftRemoteVCGTxClientPackets        Counter32,
				rcftRemoteVCGTxIdlePackets        Counter32,
				rcftRemoteVCGTxMgmntPackets       Counter32,
				rcftRemoteVCGTxBytes			  Counter32,
				rcftRemoteVCGFluxTimer		      Counter32
	         }

          		rcftRemoteVCGRxClientPackets    OBJECT-TYPE
				SYNTAX Counter32
				MAX-ACCESS read-only
				STATUS current
				DESCRIPTION
				"
					接收客户数据包数
				"
				::= { rcftRemoteVCGStatisticEntry 1 }

				rcftRemoteVCGRxIdlePackets    OBJECT-TYPE
				SYNTAX Counter32
				MAX-ACCESS read-only
				STATUS current
				DESCRIPTION
				"
					接收空闲数据包数
				"
				::= { rcftRemoteVCGStatisticEntry 2 }

				rcftRemoteVCGRxMgmntPackets	OBJECT-TYPE
				SYNTAX Counter32
				MAX-ACCESS read-only
				STATUS current
				DESCRIPTION
				"
					接收网管数据包数
				"
				::= { rcftRemoteVCGStatisticEntry 3 }

				rcftRemoteVCGRxFCSErrMgmntPackets  OBJECT-TYPE
				SYNTAX Counter32
				MAX-ACCESS read-only
				STATUS current
				DESCRIPTION
				"
					 接收FCS错误包数
				"
				::= { rcftRemoteVCGStatisticEntry 4 }

				rcftRemoteVCGRxLenErrPackets   	OBJECT-TYPE
				SYNTAX Counter32
				MAX-ACCESS read-only
				STATUS current
				DESCRIPTION
				"
					 接收长度错误包数
				"
				::= { rcftRemoteVCGStatisticEntry 5 }

				rcftRemoteVCGRxFCSErrClientPackets  OBJECT-TYPE
				SYNTAX Counter32
				MAX-ACCESS read-only
				STATUS current
				DESCRIPTION
				"
					  接收FCS错误客户数据包数
				"
				::= { rcftRemoteVCGStatisticEntry 6 }

				rcftRemoteVCGRxThecErrPackets     OBJECT-TYPE
				SYNTAX Counter32
				MAX-ACCESS read-only
				STATUS current
				DESCRIPTION
				"
					 接收类型域错误包数
				"
				::= { rcftRemoteVCGStatisticEntry 7 }

				rcftRemoteVCGRxEhecErrPackets     OBJECT-TYPE
				SYNTAX Counter32
				MAX-ACCESS read-only
				STATUS current
				DESCRIPTION
				"
					 接收扩展类型域错误包数
				"
				::= { rcftRemoteVCGStatisticEntry 8 }

				rcftRemoteVCGRxCIDErrPackets      OBJECT-TYPE
				SYNTAX Counter32
				MAX-ACCESS read-only
				STATUS current
				DESCRIPTION
				"
					  	接收客户数据帧扩展域CID与期望值不同错误包数
				"
				::= { rcftRemoteVCGStatisticEntry 9 }

				rcftRemoteVCGRxSpareErrPackets    OBJECT-TYPE
				SYNTAX Counter32
				MAX-ACCESS read-only
				STATUS current
				DESCRIPTION
				"
					 	接收客户数据帧扩展域Spare与期望值不同错误包数
				"
				::= { rcftRemoteVCGStatisticEntry 10 }

				rcftRemoteVCGRxChecCorPackets     OBJECT-TYPE
				SYNTAX Counter32
				MAX-ACCESS read-only
				STATUS current
				DESCRIPTION
				"
					 	接收帧头纠错包数
				"
				::= { rcftRemoteVCGStatisticEntry 11 }

				rcftRemoteVCGRxThecCorPackets     OBJECT-TYPE
				SYNTAX Counter32
				MAX-ACCESS read-only
				STATUS current
				DESCRIPTION
				"
					  	接收类型域纠错包数
				"
				::= { rcftRemoteVCGStatisticEntry 12 }

				rcftRemoteVCGRxEhecCorPackets     OBJECT-TYPE
				SYNTAX Counter32
				MAX-ACCESS read-only
				STATUS current
				DESCRIPTION
				"
					  	接收扩展域纠错包数
				"
				::= { rcftRemoteVCGStatisticEntry 13 }

				rcftRemoteVCGRxBytes          OBJECT-TYPE
				SYNTAX Counter32
				MAX-ACCESS read-only
				STATUS current
				DESCRIPTION
				"
					  	接收字节数
				"
				::= { rcftRemoteVCGStatisticEntry 14 }

				rcftRemoteVCGTxClientPackets        OBJECT-TYPE
				SYNTAX Counter32
				MAX-ACCESS read-only
				STATUS current
				DESCRIPTION
				"
					 	发送客户包数
				"
				::= { rcftRemoteVCGStatisticEntry 15 }

				rcftRemoteVCGTxIdlePackets        OBJECT-TYPE
				SYNTAX Counter32
				MAX-ACCESS read-only
				STATUS current
				DESCRIPTION
				"
					 	发送空闲包数
				"
				::= { rcftRemoteVCGStatisticEntry 16 }

				rcftRemoteVCGTxMgmntPackets    OBJECT-TYPE
				SYNTAX Counter32
				MAX-ACCESS read-only
				STATUS current
				DESCRIPTION
				"
					 	发送空闲包数
				"
				::= { rcftRemoteVCGStatisticEntry 17 }

				rcftRemoteVCGTxBytes				OBJECT-TYPE
				SYNTAX Counter32
				MAX-ACCESS read-only
				STATUS current
				DESCRIPTION
				"
					 	发送字节数
				"
				::= { rcftRemoteVCGStatisticEntry 18 }

    	        rcftRemoteVCGFluxTimer		   OBJECT-TYPE
				SYNTAX Counter32
				MAX-ACCESS read-only
				STATUS current
				DESCRIPTION
				"
					 流量统计时间
				"
				::= { rcftRemoteVCGStatisticEntry 19 }


     --------------------------VCG 的告警------------------------

       rcftRemoteVCGGIDTraps 	NOTIFICATION-TYPE
      	OBJECTS{
			rcftRemoteVCGAlarmStatus
      	}
      	STATUS current
     	DESCRIPTION
     	"
     		VCG成员的 的VCG-ID 错误 GID告警
     	"
     	::= { rcftRemoteVCGTraps 1 }

     	rcftRemoteVCGLOATraps 	NOTIFICATION-TYPE
      	OBJECTS{
			rcftRemoteVCGAlarmStatus
      	}
      	STATUS current
     	DESCRIPTION
     	"
     		VCG成员的 的LOA告警
     		LOA：VCAT使能时，成员相对延时差超过设定范围告警的或。
     	"
     	::= { rcftRemoteVCGTraps 2 }

     	rcftRemoteVCGLFDTraps 	NOTIFICATION-TYPE
      	OBJECTS{
			rcftRemoteVCGAlarmStatus
      	}
      	STATUS current
     	DESCRIPTION
     	"
     		VCG成员的 的LFD告警
     		LFD：GFP帧定界告警
     	"
     	::= { rcftRemoteVCGTraps 3 }
       rcftRemoteVCGCSFTraps 	NOTIFICATION-TYPE
      	OBJECTS{
			rcftRemoteVCGAlarmStatus
      	}
      	STATUS current
     	DESCRIPTION
     	"
     		VCG成员的 的CSF告警
     		CSF：GFP客户信号失效告警
     	"
     	::= { rcftRemoteVCGTraps 4 }

     	rcftRemoteVCGTLCTTraps 	NOTIFICATION-TYPE
      	OBJECTS{
			rcftRemoteVCGAlarmStatus
      	}
      	STATUS current
     	DESCRIPTION
     	"
     		TLCT：VCG发送全部成员实效告警
     	"
     	::= { rcftRemoteVCGTraps 5 }

        rcftRemoteVCGTLCRTraps 	NOTIFICATION-TYPE
      	OBJECTS{
			rcftRemoteVCGAlarmStatus
      	}
      	STATUS current
     	DESCRIPTION
     	"
     		TLCR：VCG发送全部成员实效告警
     	"
     	::= { rcftRemoteVCGTraps 6 }

        rcftRemoteVCGToLGIDTraps	NOTIFICATION-TYPE
      	OBJECTS{
			rcftRemoteVCGAlarmStatus
      	}
      	STATUS current
     	DESCRIPTION
     	"
     		对端GID告警，
     		1：恢复，2：告警
     	"
     	::= { rcftRemoteVCGTraps 7 }

		rcftRemoteVCGToLLOATraps	NOTIFICATION-TYPE
      	OBJECTS{
			rcftRemoteVCGAlarmStatus
      	}
      	STATUS current
     	DESCRIPTION
     	"
     		对端VCG LOA告警
     		1：恢复，2：告警
     	"
     	::= { rcftRemoteVCGTraps 8 }

		rcftRemoteVCGToLLFDTraps	NOTIFICATION-TYPE
      	OBJECTS{
			rcftRemoteVCGAlarmStatus
      	}
      	STATUS current
     	DESCRIPTION
     	"
     		对端VCG  LFP告警
    		1：恢复，2：告警
       	"
     	::= { rcftRemoteVCGTraps 9 }






   --------------------------VCG 成员的告警------------------------

       rcftRemoteVCGMemberLOMTraps 	NOTIFICATION-TYPE
      	OBJECTS{
			rcftRemoteVCGMemberAlarmStatus
      	}
      	STATUS current
     	DESCRIPTION
     	"
     		VCG成员的 的复帧失步LOM 告警
     	"
     	::= { rcftRemoteVCGTraps 10 }

     	rcftRemoteVCGMemberSQMTraps 	NOTIFICATION-TYPE
      	OBJECTS{
			rcftRemoteVCGMemberAlarmStatus
      	}
      	STATUS current
     	DESCRIPTION
     	"
     		VCG成员的 的SQM告警
     		SQM ：VCAT使能时，成员的SQ值不符告警。
     	"
     	::= { rcftRemoteVCGTraps 11 }

     	rcftRemoteVCGMemberCRCTraps 	NOTIFICATION-TYPE
      	OBJECTS{
			rcftRemoteVCGMemberAlarmStatus
      	}
      	STATUS current
     	DESCRIPTION
     	"
     		VCG成员的 的CRC告警
       	"
     	::= { rcftRemoteVCGTraps 12 }

     	rcftRemoteVCGMemberLOATraps 	NOTIFICATION-TYPE
      	OBJECTS{
			rcftRemoteVCGMemberAlarmStatus
      	}
      	STATUS current
     	DESCRIPTION
     	"
     		VCG成员的 的LOA告警
     		LOA：成员的相对延时差超过设定范围告警

       	"
     	::= { rcftRemoteVCGTraps 13 }

        rcftRemoteVCGToLMemberLOMTraps 	NOTIFICATION-TYPE
      	OBJECTS{
			rcftRemoteToLVCGMemberAlarmStatus
      	}
      	STATUS current
     	DESCRIPTION
     	"
     		对端VCG成员的 的LOA告警
     		LOA：成员的相对延时差超过设定范围告警

       	"
     	::= { rcftRemoteVCGTraps 14 }

  		rcftRemoteVCGToLMemberSQMTraps 	NOTIFICATION-TYPE
      	OBJECTS{
			rcftRemoteToLVCGMemberAlarmStatus
      	}
      	STATUS current
     	DESCRIPTION
     	"
     		对端VCG成员的 的LOA告警
     		LOA：成员的相对延时差超过设定范围告警

       	"
     	::= { rcftRemoteVCGTraps 15 }

  		rcftRemoteVCGToLMemberCRCTraps 	NOTIFICATION-TYPE
      	OBJECTS{
			rcftRemoteToLVCGMemberAlarmStatus
      	}
      	STATUS current
     	DESCRIPTION
     	"
     		对端VCG成员的 的LOA告警
     		LOA：成员的相对延时差超过设定范围告警

       	"
     	::= { rcftRemoteVCGTraps 16 }

   		rcftRemoteVCGToLMemberLOATraps 	NOTIFICATION-TYPE
      	OBJECTS{
			rcftRemoteToLVCGMemberAlarmStatus
      	}
      	STATUS current
     	DESCRIPTION
     	"
     		对端VCG成员的 的LOA告警
     		LOA：成员的相对延时差超过设定范围告警

       	"
     	::= { rcftRemoteVCGTraps 17 }

 END
