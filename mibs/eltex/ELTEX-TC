ELTEX-TC DEFINITIONS ::= BEGIN

-- Title:   ELTEX Textual Conventions
-- Version: 1.0
-- Date:    19 April 2017

IMPORTS
    MODULE-IDENTITY,
    OBJECT-TYPE,
    NOTIFICATION-TYPE,
    Gauge32
        FROM SNMPv2-SMI

    TEXTUAL-CONVENTION
        FROM SNMPv2-TC

    eltexLtd
        FROM ELTEX-SMI-ACTUAL;


eltexTC MODULE-IDENTITY
    LAST-UPDATED "201704190000Z"
    ORGANIZATION "Eltex Enterprise, Ltd."
    CONTACT-INFO
        "www.eltex.nsk.ru"
    DESCRIPTION
        "The MIB module for managing all Textual Conventions of Eltex Enterprise."
    REVISION     "201704190000Z"
    DESCRIPTION "Initial revision of ELTEX-TC"
    ::= { eltexLtd 8 }

--
-- Textual Conventions
--
EltexPercent ::= TEXTUAL-CONVENTION
    STATUS       current
    DESCRIPTION
        "This object changes in range of value (0..100)."
    SYNTAX       Gauge32 (0..100)

EltexThresholdRelation ::= TEXTUAL-CONVENTION
    STATUS       current
    DESCRIPTION
        "Threshold relational operator types.  valid values are:

        lessThan(1):        if the sensor value is less than
                            the threshold value
        lessOrEqual(2):     if the sensor value is less than or equal to
                            the threshold value
        greaterThan(3):     if the sensor value is greater than
                            the threshold value
        greaterOrEqual(4):  if the sensor value is greater than or equal
                            to the threshold value
        equalTo(5):         if the sensor value is equal to
                            the threshold value
        notEqualTo(6):      if the sensor value is not equal to
                            the threshold value"
    SYNTAX      INTEGER {
                    lessThan(1),
                    lessOrEqual(2),
                    greaterThan(3),
                    greaterOrEqual(4),
                    equalTo(5),
                    notEqualTo(6)
                }
END
