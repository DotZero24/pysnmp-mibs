ELTEX-MES-SNMP-MIB DEFINITIONS ::= BEGIN

-- Title:      ELTEX MES SNMP Private MIB
-- Version:    1.0
-- Date:       23 October 2019

IMPORTS
    MODULE-IDENTITY,
    OBJECT-TYPE
      FROM SNMPv2-SMI

    AutonomousType
      FROM SNMPv2-TC

    usmUserEntry
      FROM SNMP-USER-BASED-SM-MIB

    eltMesMng
      FROM ELTEX-MES;


eltMesSnmp MODULE-IDENTITY
          LAST-UPDATED "201910230000Z"
          ORGANIZATION "Eltex Enterprise Co, Ltd."
          CONTACT-INFO
                  "eltex-co.ru"
          DESCRIPTION
                  "This MIB module contains SNMP MIB
                   definitions for Eltex Enterprise."
          ::= { eltMesMng 12 }

-------------------------------------------------------------------------------

eltMesSnmpMIBObjects           OBJECT IDENTIFIER ::= { eltMesSnmp 1 }
eltMesSnmpMIBNotifications     OBJECT IDENTIFIER ::= { eltMesSnmp 2 }

-- SNMP Users Objects

eltMesSnmpUser                 OBJECT IDENTIFIER ::= { eltMesSnmpMIBObjects 1 }

-- SNMP Users Global Defintions

eltMesSnmpUserGlobals          OBJECT IDENTIFIER ::= { eltMesSnmpUser 1 }

-- SNMP Users Configuration

eltMesSnmpUserConfig           OBJECT IDENTIFIER ::= { eltMesSnmpUser 2 }

eltSnmpUserTable OBJECT-TYPE
    SYNTAX       SEQUENCE OF EltSnmpUserEntry
    MAX-ACCESS   not-accessible
    STATUS       current
    DESCRIPTION "The table of users configured in the SNMP local database."
    ::= { eltMesSnmpUserConfig 1 }

eltSnmpUserEntry OBJECT-TYPE
    SYNTAX       EltSnmpUserEntry
    MAX-ACCESS   not-accessible
    STATUS       current
    DESCRIPTION "This entry augments existing usmUserEntry defined in RFC2574"
    AUGMENTS    { usmUserEntry }
    ::= { eltSnmpUserTable 1 }

EltSnmpUserEntry ::= SEQUENCE {
    eltSnmpUserPrivProtocol             AutonomousType
}

eltSnmpUserPrivProtocol OBJECT-TYPE
    SYNTAX       AutonomousType
    MAX-ACCESS   read-create
    STATUS       current
    DESCRIPTION "An indication of whether messages sent on behalf of
                 this user to/from the SNMP engine identified by
                 usmUserEngineID, can be protected from disclosure,
                 and if so, the type of privacy protocol which is used."
    DEFVAL      { usmNoPrivProtocol }
    ::= { eltSnmpUserEntry 1 }

END
