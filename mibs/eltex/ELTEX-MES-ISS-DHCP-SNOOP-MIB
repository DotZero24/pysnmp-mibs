ELTEX-MES-ISS-DHCP-SNOOP-MIB DEFINITIONS ::= BEGIN

IMPORTS
    MODULE-IDENTITY, OBJECT-TYPE, Integer32
        FROM SNMPv2-SMI
    ifIndex
        FROM IF-MIB
    eltMesIss
        FROM ELTEX-MES-ISS-MIB;

eltMesIssDhcpSnoopMIB MODULE-IDENTITY
    LAST-UPDATED "202210050000Z"
    ORGANIZATION "Eltex Enterprise, Ltd."
    CONTACT-INFO
        "eltex-co.ru"
    DESCRIPTION
        "Eltex MIB extension to configure DHCP Snooping functionality."
    REVISION "202210050000Z"
    DESCRIPTION "Initial Revision."
    ::= { eltMesIss 32 }

-- ========================================================================== --
--                             Groups in the MIB                              --
-- ========================================================================== --

eltMesIssDhcpSnoopObjects OBJECT IDENTIFIER ::= { eltMesIssDhcpSnoopMIB 1 }

eltMesIssDhcpSnoopGlobals          OBJECT IDENTIFIER ::= { eltMesIssDhcpSnoopObjects 1 }
eltMesIssDhcpSnoopInterfaceConfigs OBJECT IDENTIFIER ::= { eltMesIssDhcpSnoopObjects 2 }

-- ========================================================================== --
--                   Dhcp Snooping interface configurations                   --
-- ========================================================================== --

eltMesIssDhcpSnoopInterfaceTable OBJECT-TYPE
    SYNTAX      SEQUENCE OF EltMesIssDhcpSnoopInterfaceEntry
    MAX-ACCESS  not-accessible
    STATUS      current
    DESCRIPTION
    "This table contains the configuration
     parameters of DHCP snooping per port."
    ::= { eltMesIssDhcpSnoopInterfaceConfigs 1 }

eltMesIssDhcpSnoopInterfaceEntry OBJECT-TYPE
    SYNTAX      EltMesIssDhcpSnoopInterfaceEntry
    MAX-ACCESS  not-accessible
    STATUS      current
    DESCRIPTION
    "Each entry in this table shows the status of dhcp
     snooping on the port."
    INDEX { ifIndex }
    ::= { eltMesIssDhcpSnoopInterfaceTable 1 }

EltMesIssDhcpSnoopInterfaceEntry ::= SEQUENCE {
        eltMesIssDhcpSnoopInterfaceStatus        INTEGER
    }

eltMesIssDhcpSnoopInterfaceStatus OBJECT-TYPE
    SYNTAX      INTEGER { enabled (1), disabled (2) }
    MAX-ACCESS  read-write
    STATUS      current
    DESCRIPTION
    "This object is used to enable or disable DHCP snooping
     per port."
    DEFVAL  { disabled }
    ::= { eltMesIssDhcpSnoopInterfaceEntry 1 }

END
