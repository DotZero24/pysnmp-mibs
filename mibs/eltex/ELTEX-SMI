--
-- Eltex Enterprise Specific MIB: Structure of Management Information
--
-- Copyright (c) 2007-2009, Eltex Co
--
-- The contents of this document are subject to change without notice.
--

ELTEX-SMI DEFINITIONS ::= BEGIN

IMPORTS
	enterprises,
	MODULE-IDENTITY,
	OBJECT-IDENTITY,
	OBJECT-TYPE,
	NOTIFICATION-TYPE,
	Integer32
		FROM SNMPv2-SMI
	DisplayString,
	TimeStamp
		FROM SNMPv2-TC
	OBJECT-GROUP,
	NOTIFICATION-GROUP
		FROM SNMPv2-CONF;

eltex MODULE-IDENTITY
	LAST-UPDATED "200906031500Z"
	ORGANIZATION "Eltex Co"
	CONTACT-INFO
		"eltex@gcom.ru"
	DESCRIPTION
		"The Structure of Management Information for Eltex Networks."
	::= { enterprises 34300 }


--
-- Eltex MIB tree structure
--

elHardware OBJECT-IDENTITY
	STATUS  current
	DESCRIPTION
		"The root of eltex hardware OIDs."
	::= { eltex 1 }

elSoftware OBJECT-IDENTITY
	STATUS  current
	DESCRIPTION
		"The root of eltex software OIDs."
	::= { eltex 2 }

eltrapGroup OBJECT-IDENTITY
	STATUS  current
	DESCRIPTION
		"The root of eltex traps objects."
	::= { eltex 3 }

-- define trap groups --
mc240AlarmTraps OBJECT IDENTIFIER 	::= { eltrapGroup 3 }


-- define all traps ---- MC-240 traps --
mc240StreamAlarmTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 stream alarm trap. Severity: alert"
	::= { mc240AlarmTraps 1 }


mc240SyncAlarmTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 sync alarm trap. Severity: warning"
	::= { mc240AlarmTraps 2 }


mc240ss7LinkAlarmTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 ss7 link alarm trap. Severity: alert"
	::= { mc240AlarmTraps 3 }


mc240ss7LinksetAlarmTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 ss7 linkset alarm trap. Severity: critical"
	::= { mc240AlarmTraps 4 }


mc240FileAlarmTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 file alarm trap. Severity: critical"
	::= { mc240AlarmTraps 5 }


mc240CardAlarmTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 card alarm trap. Severity: critical"
	::= { mc240AlarmTraps 6 }


mxlDPSAlarmTrap NOTIFICATION-TYPE
	OBJECTS {
		mcTrapExState,
		mcTrapLParam1,
		mcTrapLParam2,
		mcTrapLParam3,
		mcTrapID,
		mcTrapDescr}
	STATUS  current
	DESCRIPTION
		"mxl DSL DP system alarm trap"
	::= { mc240AlarmTraps 7 }


mxlTELEAlarmTrap NOTIFICATION-TYPE
	OBJECTS {
		mcTrapExState,
		mcTrapLParam1,
		mcTrapLParam2,
		mcTrapLParam3,
		mcTrapID,
		mcTrapDescr}
	STATUS  current
	DESCRIPTION
		"mxl DSL DP system alarm trap"
	::= { mc240AlarmTraps 8 }


mc240UPSAlarmTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc240 UPS alarm trap"
	::= { mc240AlarmTraps 9 }


mc240SensAlarmTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc240 sensor alarm trap (mcTrapExState = sensors bit mask, param1=temp,C, param2=Hum,%)"
	::= { mc240AlarmTraps 10 }


-- ---- ---- ---- ---- ---- ---- MXA link alarm ---- ---- ---- ---- ---- ---- ---- --
dslamLinkDownTrap NOTIFICATION-TYPE
	OBJECTS {
		mcTrapExState,
		mcTrapLParam1,
		mcTrapLParam2,
		mcTrapLParam3,
		mcTrapID,
		mcTrapDescr}
	STATUS  current
	DESCRIPTION
		"dslam link down trap (mcTrapExState = link state, param1 = ADSLport)"
	::= { mc240AlarmTraps 11 }

-- MXA change adsl port Downstream rate alarm --
dslamDSRateAlarmTrap NOTIFICATION-TYPE
	OBJECTS {
		mcTrapExState,
		mcTrapLParam1,
		mcTrapLParam2,
		mcTrapLParam3,
		mcTrapID,
		mcTrapDescr}
	STATUS  current
	DESCRIPTION
		"Downstream rate for dslam ADSL port change (mcTrapExState = 2-increase 1-decrease, param1 = ADSLport)"
	::= { mc240AlarmTraps 12 }


-- MXA change adsl port Upstream rate alarm --
dslamUSRateAlarmTrap NOTIFICATION-TYPE
	OBJECTS {
		mcTrapExState,
		mcTrapLParam1,
		mcTrapLParam2,
		mcTrapLParam3,
		mcTrapID,
		mcTrapDescr}
	STATUS  current
	DESCRIPTION
		"Downstream rate for dslam ADSL port change (mcTrapExState = 2-increase 1-decrease, param1 = ADSLport)"
	::= { mc240AlarmTraps 13 }


-- ---- ---- ---- ---- ---- ---- ----  GePON ALARMS ---- ---- ---- ---- ---- ---- ---- ----
-- GePON ONU Authorization Alarm  --
ponONUAuthAlarmTrap NOTIFICATION-TYPE
	OBJECTS {
		mcTrapExState,
		mcTrapLParam1,
		mcTrapLParam2,
		mcTrapLParam3,
		mcTrapID,
		mcTrapDescr}
	STATUS  current
	DESCRIPTION
		"Bad registration ONU Event (mcTrapLParam1=Optical Interface Number, mcTrapDescr='description with MAC addr ONU')"
	::= { mc240AlarmTraps 14 }


-- GePON Eth link Down  --
ponEthAlarmTrap NOTIFICATION-TYPE
	OBJECTS {
		mcTrapExState,
		mcTrapLParam1,
		mcTrapLParam2,
		mcTrapLParam3,
		mcTrapID,
		mcTrapDescr}
	STATUS  current
	DESCRIPTION
		"Eth Link Down, mcTrapLParam1=Link Number, Description='GePON: Eth Link N down'"
	::= { mc240AlarmTraps 15 }


-- GePON Optical link Event  --
ponOpticalAlarmTrap NOTIFICATION-TYPE
	OBJECTS {
		mcTrapExState,
		mcTrapLParam1,
		mcTrapLParam2,
		mcTrapLParam3,
		mcTrapID,
		mcTrapDescr}
	STATUS  current
	DESCRIPTION
		"The optical link N (mcTrapLParam1) has no active devices"
	::= { mc240AlarmTraps 16 }

-- ---- ---- ---- ---- ---- ---- MXA ---- ---- ---- ---- ---- ---- ---- --
-- MXA overheat alarm --
dslamOverheatAlarmTrap NOTIFICATION-TYPE
	OBJECTS {
		mcTrapExState,
		mcTrapLParam1,
		mcTrapLParam2,
		mcTrapLParam3,
		mcTrapID,
		mcTrapDescr}
	STATUS  current
	DESCRIPTION
		"overheat (mcTrapExState = 1 -> DSP, = 2 -> PWR, param1 = val of temp * 10)"
	::= { mc240AlarmTraps 17 }


-- MXA power alarm --
dslamVoltageAlarmTrap NOTIFICATION-TYPE
	OBJECTS {
		mcTrapExState,
		mcTrapLParam1,
		mcTrapLParam2,
		mcTrapLParam3,
		mcTrapID,
		mcTrapDescr}
	STATUS  current
	DESCRIPTION
		"when voltage deviation become more 10% (param1 = number of voltage nominal mean  12, -12, 3.3, 2.5, 1.8, 1.25, 1.5, 1 correspondly, param2 - whole number part temperature value, param3 - decimal part  temperature value )"
	::= { mc240AlarmTraps 18 }


-- MXA session connect --
dslamSessionAlarmTrap NOTIFICATION-TYPE
	OBJECTS {
		mcTrapExState,
		mcTrapLParam1,
		mcTrapLParam2,
		mcTrapLParam3,
		mcTrapID,
		mcTrapDescr}
	STATUS  current
	DESCRIPTION
		"Trap sending when connection happen, mcTrapLParam1 - means connection from (0)-CLI (1)->Webs (2)->SNMP"
	::= { mc240AlarmTraps 19 }

-- MXA Eth OperStatus --
dslamEthLinkAlarmTrap NOTIFICATION-TYPE
	OBJECTS {
		mcTrapExState,
		mcTrapLParam1,
		mcTrapLParam2,
		mcTrapLParam3,
		mcTrapID,
		mcTrapDescr}
	STATUS  current
	DESCRIPTION
		"Trap sending when switch port link DOWN, mcTrapLParam1 - means port num:
		for mxa: 0 - p0; 1 - p1; 2 - p2; 3 - cpu; 4 - dsl0; 5 - sfp;  6 - dsl1;
		for asl: 0 - lan;                3 - cpu; 4 - dsl0; 5 - dsl1; 6 - s0; 7 - s1"
	::= { mc240AlarmTraps 20 }

mc240OkTraps OBJECT IDENTIFIER 	::= { eltrapGroup 4 }


mc240StreamOkTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 stream ok trap. Severity: alert"
	::= { mc240OkTraps 1 }


mc240SyncOkTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 sync ok trap. Severity: warning"
	::= { mc240OkTraps 2 }


mc240ss7LinkOkTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 ss7 link ok trap. Severity: alert"
	::= { mc240OkTraps 3 }


mc240ss7LinksetOkTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 ss7 linkset ok trap. Severity: critical"
	::= { mc240OkTraps 4 }


mc240FileOkTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 file ok trap. Severity: critical"
	::= { mc240OkTraps 5 }


mc240CardOkTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc-240 card trap. Severity: critical"
	::= { mc240OkTraps 6 }


mxlDPSOkTrap NOTIFICATION-TYPE
	OBJECTS {
		mcTrapExState,
		mcTrapLParam1,
		mcTrapLParam2,
		mcTrapLParam3,
		mcTrapID,
		mcTrapDescr}
	STATUS  current
	DESCRIPTION
		"mxl DSL DP system alarm trap (normal state)"
	::= { mc240OkTraps 7 }


mxlTELEOkTrap NOTIFICATION-TYPE
	OBJECTS {
		mcTrapExState,
		mcTrapLParam1,
		mcTrapLParam2,
		mcTrapLParam3,
		mcTrapID,
		mcTrapDescr}
	STATUS  current
	DESCRIPTION
		"mxl DSL DP system alarm trap (normal state)"
	::= { mc240OkTraps 8 }


mc240UPSOkTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc240 UPS alarm trap (normal state)"
	::= { mc240OkTraps 9 }


mc240SensOkTrap NOTIFICATION-TYPE
	OBJECTS {
		mcTrapExState,
		mcTrapLParam1,
		mcTrapLParam2,
		mcTrapLParam3,
		mcTrapID,
		mcTrapDescr,
		mcTrapRestoredAlarmID,
		mcTrapSyncType,
		mcReservedFlag}
	STATUS  current
	DESCRIPTION
		"mc240 sensor alarm trap (normal state)"
	::= { mc240OkTraps 10 }


dslamLinkUpTrap NOTIFICATION-TYPE
	OBJECTS {
		mcTrapExState,
		mcTrapLParam1,
		mcTrapLParam2,
		mcTrapLParam3,
		mcTrapID,
		mcTrapDescr}
	STATUS  current
	DESCRIPTION
		"dslam link up trap (mcTrapExState = link state == 0, param1 = ADSLport)"
	::= { mc240OkTraps 11 }


dslamDSRateOkTrap NOTIFICATION-TYPE
	OBJECTS {
		mcTrapExState,
		mcTrapLParam1,
		mcTrapLParam2,
		mcTrapLParam3,
		mcTrapID,
		mcTrapDescr}
	STATUS  current
	DESCRIPTION
		"Downstream rate for dslam ADSL port change (mcTrapExState = 0-reate not change, param1 = ADSLport)"
	::= { mc240OkTraps 12 }


dslamUSRateOkTrap NOTIFICATION-TYPE
	OBJECTS {
		mcTrapExState,
		mcTrapLParam1,
		mcTrapLParam2,
		mcTrapLParam3,
		mcTrapID,
		mcTrapDescr}
	STATUS  current
	DESCRIPTION
		"Downstream rate for dslam ADSL port change (mcTrapExState = 0-reate not change, param1 = ADSLport)"
	::= { mc240OkTraps 13 }


-- PON ok traps --
ponONUAuthOkTrap NOTIFICATION-TYPE
	OBJECTS {
		mcTrapExState,
		mcTrapLParam1,
		mcTrapLParam2,
		mcTrapLParam3,
		mcTrapID,
		mcTrapDescr}
	STATUS  current
	DESCRIPTION
		"Normal registration ONU Event (mcTrapLParam1=Optical Interface Number, mcTrapDescr='description with MAC addr ONU')"
	::= { mc240OkTraps 14 }


ponEthOkTrap NOTIFICATION-TYPE
	OBJECTS {
		mcTrapExState,
		mcTrapLParam1,
		mcTrapLParam2,
		mcTrapLParam3,
		mcTrapID,
		mcTrapDescr}
	STATUS  current
	DESCRIPTION
		"Eth Link Up, mcTrapLParam1=Link Number, Description='GePON: Eth Link N up'"
	::= { mc240OkTraps 15 }


ponOpticalOkTrap NOTIFICATION-TYPE
	OBJECTS {
		mcTrapExState,
		mcTrapLParam1,
		mcTrapLParam2,
		mcTrapLParam3,
		mcTrapID,
		mcTrapDescr}
	STATUS  current
	DESCRIPTION
		"The optical link N (mcTrapLParam1) has M (mcTrapLParam2) active devices"
	::= { mc240OkTraps 16 }

-- MXA
dslamOverheatOkTrap NOTIFICATION-TYPE
	OBJECTS {
		mcTrapExState,
		mcTrapLParam1,
		mcTrapLParam2,
		mcTrapLParam3,
		mcTrapID,
		mcTrapDescr}
	STATUS  current
	DESCRIPTION
		"overheat (mcTrapExState = 1 -> DSP, = 2 -> PWR, param1 = val of temp * 10)"
	::= { mc240OkTraps 17 }

dslamVoltageOkTrap NOTIFICATION-TYPE
	OBJECTS {
		mcTrapExState,
		mcTrapLParam1,
		mcTrapLParam2,
		mcTrapLParam3,
		mcTrapID,
		mcTrapDescr}
	STATUS  current
	DESCRIPTION
		"when voltage deviation become less 10% (param1 = number of voltage nominal mean  12, -12, 3.3, 2.5, 1.8, 1.25, 1.5, 1 correspondly, param2 - whole number part temperature value, param3 - decimal part  temperature value )"
	::= { mc240OkTraps 18 }


-- MXA session connect --
dslamSessionOkTrap NOTIFICATION-TYPE
	OBJECTS {
		mcTrapExState,
		mcTrapLParam1,
		mcTrapLParam2,
		mcTrapLParam3,
		mcTrapID,
		mcTrapDescr}
	STATUS  current
	DESCRIPTION
		"Trap sending when connection closed, mcTrapLParam1 - means disconnection from (0)-CLI (1)->Webs (2)->SNMP"
	::= { mc240OkTraps 19 }

-- MXA Eth OperStatus --
dslamEthLinkOkTrap NOTIFICATION-TYPE
	OBJECTS {
		mcTrapExState,
		mcTrapLParam1,
		mcTrapLParam2,
		mcTrapLParam3,
		mcTrapID,
		mcTrapDescr}
	STATUS  current
	DESCRIPTION
		"Trap sending when switch port link UP, mcTrapLParam1 - means port num:
		for mxa: 0 - p0; 1 - p1; 2 - p2; 3 - cpu; 4 - dsl0; 5 - sfp;  6 - dsl1;
		for asl: 0 - lan;                3 - cpu; 4 - dsl0; 5 - dsl1; 6 - s0; 7 - s1"
	::= { mc240OkTraps 20 }

mc240TrapTypes OBJECT IDENTIFIER 	::= { eltrapGroup 5 }

-- trap properties

mcTrapExState OBJECT-TYPE
	SYNTAX  Integer32
	MAX-ACCESS read-only
	STATUS  current
	DESCRIPTION
		"state (additional state)"
	::= { mc240TrapTypes 1 }


mcTrapLParam1 OBJECT-TYPE
	SYNTAX  Integer32
	MAX-ACCESS read-only
	STATUS  current
	DESCRIPTION
		"param-1 (slot or index)"
	::= { mc240TrapTypes 2 }


mcTrapLParam2 OBJECT-TYPE
	SYNTAX  Integer32
	MAX-ACCESS read-only
	STATUS  current
	DESCRIPTION
		"param-2 (port or index)"
	::= { mc240TrapTypes 3 }


mcTrapLParam3 OBJECT-TYPE
	SYNTAX  Integer32
	MAX-ACCESS read-only
	STATUS  current
	DESCRIPTION
		"param-3 (other index)"
	::= { mc240TrapTypes 4 }


mcTrapID OBJECT-TYPE
	SYNTAX  Integer32
	MAX-ACCESS read-only
	STATUS  current
	DESCRIPTION
		"ID (pbx trap id)"
	::= { mc240TrapTypes 5 }


mcTrapDescr OBJECT-TYPE
	SYNTAX  DisplayString (SIZE (0..255))
	MAX-ACCESS read-only
	STATUS  current
	DESCRIPTION
		"Alarm description"
	::= { mc240TrapTypes 6 }


mcTrapRestoredAlarmID OBJECT-TYPE
	SYNTAX  Integer32
	MAX-ACCESS read-only
	STATUS  current
	DESCRIPTION
		"If this restore event then here writed Alarm ID. If this alarm event then mcTrapRestoredAlarmID=0."
	::= { mc240TrapTypes 7 }


mcTrapSyncType OBJECT-TYPE
	SYNTAX  Integer32
	MAX-ACCESS read-only
	STATUS  current
	DESCRIPTION
		"Type of trap: 0 - Normal; 1 - Journal alarms; 2 - Active alarms"
	::= { mc240TrapTypes 8 }


mcReservedFlag OBJECT-TYPE
	SYNTAX  Integer32
	MAX-ACCESS read-only
	STATUS  current
	DESCRIPTION
		"Reserved flag"
	::= { mc240TrapTypes 9 }


-- OMS operation status traps --

omsOperationAlarmTraps OBJECT IDENTIFIER 	::= { eltrapGroup 20 }
omsOperationOkTraps OBJECT IDENTIFIER 	::= { eltrapGroup 21 }


omsOperationCommandAlarm NOTIFICATION-TYPE
	OBJECTS {
		mcTrapExState,
		mcTrapLParam1,
		mcTrapLParam2,
		mcTrapLParam3,
		mcTrapID,
		mcTrapDescr}
	STATUS  current
	DESCRIPTION
		"   mcTrapLParam1 = command <upload=1, download=2, apply=3, confirm=4, save=5>;
                    mcTrapLParam2 = filetype <pattern=1, private=2, binary=3>
                    mcTrapDescr = Description of operarion:
                        DeviceName,
                        command <upload, download, apply, confirm, save>,
                        tftp host,
                        config filename,
                        status=Error,
                        cause of error"
	::= { omsOperationAlarmTraps 1 }

omsOperationCommandOk NOTIFICATION-TYPE
	OBJECTS {
		mcTrapExState,
		mcTrapLParam1,
		mcTrapLParam2,
		mcTrapLParam3,
		mcTrapID,
		mcTrapDescr}
	STATUS  current
	DESCRIPTION
		"   mcTrapLParam1 = command <upload=1, download=2, apply=3, confirm=4, save=5>;
                    mcTrapLParam2 = filetype <pattern=1, private=2, binary=3>
                    mcTrapDescr = Description of operarion:
                        DeviceName,
                        command <upload, download, apply, confirm, save>,
                        tftp host,
                        config filename,
                        status=Ok"
	::= { omsOperationOkTraps 1 }

---------------------------------------------------------------------------------------------------------------------------
----------------------------------------------- MP800MK Traps -------------------------------------------------------------
---------------------------------------------------------------------------------------------------------------------------

-- mp800mk ALARM traps
mp800mkAlarmTraps OBJECT IDENTIFIER   ::= { eltrapGroup 8 }

		-- MP status
		mp800mkMPStatusAlarmTrap NOTIFICATION-TYPE
                        OBJECTS {
         mp800mkTrapParameter,
				 mp800mkTrapValue,
				 mp800mkTrapComment}
			STATUS		current
                        DESCRIPTION
                                "MP operation error."
                        ::=  {mp800mkAlarmTraps 1}

		-- Input parameters
		mp800mkInpParmAlarmTrap NOTIFICATION-TYPE
                        OBJECTS {
         mp800mkTrapParameter,
				 mp800mkTrapValue,
				 mp800mkTrapComment}
			STATUS		current
                        DESCRIPTION
                                "Incorrect input parameters."
                        ::=  {mp800mkAlarmTraps 2}

		-- UEP configuration
		mp800mkUEPConfAlarmTrap NOTIFICATION-TYPE
                        OBJECTS {
         mp800mkTrapParameter,
				 mp800mkTrapValue,
				 mp800mkTrapComment}
			STATUS		current
                        DESCRIPTION
                                "UEP configuration error."
                        ::=  {mp800mkAlarmTraps 3}

		-- Temperature measurement
		mp800mkTMAlarmTrap NOTIFICATION-TYPE
                        OBJECTS {
         mp800mkTrapParameter,
				 mp800mkTrapValue,
				 mp800mkTrapComment}
			STATUS		current
                        DESCRIPTION
                                "Temperature measurement error."
                        ::=  {mp800mkAlarmTraps 4}

		-- AC voltage measurement
		mp800mkACVMAlarmTrap NOTIFICATION-TYPE
                        OBJECTS {
         mp800mkTrapParameter,
				 mp800mkTrapValue,
				 mp800mkTrapComment}
			STATUS		current
                        DESCRIPTION
                                "ACV measurement error."
                        ::=  {mp800mkAlarmTraps 5}

		-- Battery current measurement
		mp800mkIbatMAlarmTrap NOTIFICATION-TYPE
                        OBJECTS {
         mp800mkTrapParameter,
				 mp800mkTrapValue,
				 mp800mkTrapComment}
			STATUS		current
                        DESCRIPTION
                                "Battery current measurement error."
                        ::=  {mp800mkAlarmTraps 6}

		-- Battery voltage measurement
		mp800mkVbatMAlarmTrap NOTIFICATION-TYPE
                        OBJECTS {
         mp800mkTrapParameter,
				 mp800mkTrapValue,
				 mp800mkTrapComment}
			STATUS		current
                        DESCRIPTION
                                "Battery voltage measurement error."
                        ::=  {mp800mkAlarmTraps 7}

		-- Battery voltage control
		mp800mkVbatChAlarmTrap NOTIFICATION-TYPE
                        OBJECTS {
         mp800mkTrapParameter,
				 mp800mkTrapValue,
				 mp800mkTrapComment}
			STATUS		current
                        DESCRIPTION
                                "Can't change (increase or decrease) battery voltage."
                        ::=  {mp800mkAlarmTraps 8}

		-- Release device status
		mp800mkRlsDevAlarmTrap NOTIFICATION-TYPE
                        OBJECTS {
         mp800mkTrapParameter,
				 mp800mkTrapValue,
				 mp800mkTrapComment}
			STATUS		current
                        DESCRIPTION
                                "Release device is off (battery disconnected)."
                        ::=  {mp800mkAlarmTraps 9}

		-- Battery cell voltage spread
		mp800mkDVcellAlarmTrap NOTIFICATION-TYPE
                        OBJECTS {
         mp800mkTrapParameter,
				 mp800mkTrapValue,
				 mp800mkTrapComment}
			STATUS		current
                        DESCRIPTION
                                "Battery cell voltage spread is out of range."
                        ::=  {mp800mkAlarmTraps 10}

		-- AC voltage
		mp800mkACVAlarmTrap NOTIFICATION-TYPE
                        OBJECTS {
         mp800mkTrapParameter,
				 mp800mkTrapValue,
				 mp800mkTrapComment}
			STATUS		current
                        DESCRIPTION
                                "AC voltage is out of range."
                        ::=  {mp800mkAlarmTraps 11}

		-- Battery charge status
		mp800mkBatChargeAlarmTrap NOTIFICATION-TYPE
                        OBJECTS {
         mp800mkTrapParameter,
				 mp800mkTrapValue,
				 mp800mkTrapComment}
			STATUS		current
                        DESCRIPTION
                                "Battery is close to total discharge."
                        ::=  {mp800mkAlarmTraps 12}

		-- Load current
		mp800mkIloadAlarmTrap NOTIFICATION-TYPE
                        OBJECTS {
         mp800mkTrapParameter,
				 mp800mkTrapValue,
				 mp800mkTrapComment}
			STATUS		current
                        DESCRIPTION
                                "Load current is out of range."
                        ::=  {mp800mkAlarmTraps 13}

		-- Battery charge current
		mp800mkIbatChAlarmTrap NOTIFICATION-TYPE
                        OBJECTS {
         mp800mkTrapParameter,
				 mp800mkTrapValue,
				 mp800mkTrapComment}
			STATUS		current
                        DESCRIPTION
                                "Battery charge current is too high."
                        ::=  {mp800mkAlarmTraps 14}

		-- Power supply status
		mp800mkSuppAlarmTrap NOTIFICATION-TYPE
                        OBJECTS {
         mp800mkTrapParameter,
				 mp800mkTrapValue,
				 mp800mkTrapComment}
			STATUS		current
                        DESCRIPTION
                                "Power supply from battery."
                        ::=  {mp800mkAlarmTraps 15}

		-- Battery disconnected?
		mp800mkBatConnAlarmTrap NOTIFICATION-TYPE
                        OBJECTS {
         mp800mkTrapParameter,
				 mp800mkTrapValue,
				 mp800mkTrapComment}
			STATUS		current
                        DESCRIPTION
                                "Battery is disconnected from MPs' output."
                        ::=  {mp800mkAlarmTraps 16}

-- mp800mk OK traps
mp800mkOkTraps   	OBJECT IDENTIFIER   ::= { eltrapGroup 9 }

		-- MP status
		mp800mkMPStatusOkTrap NOTIFICATION-TYPE
                        OBJECTS {
         mp800mkTrapParameter,
				 mp800mkTrapValue,
				 mp800mkTrapComment}
			STATUS		current
                        DESCRIPTION
                                "MP operation OK."
                        ::=  {mp800mkOkTraps 1}

		-- Input parameters
		mp800mkInpParmOkTrap NOTIFICATION-TYPE
                        OBJECTS {
         mp800mkTrapParameter,
				 mp800mkTrapValue,
				 mp800mkTrapComment}
			STATUS		current
                        DESCRIPTION
                                "Input parameters OK."
                        ::=  {mp800mkOkTraps 2}

		-- UEP configuration
		mp800mkUEPConfOkTrap NOTIFICATION-TYPE
                        OBJECTS {
         mp800mkTrapParameter,
				 mp800mkTrapValue,
				 mp800mkTrapComment}
			STATUS		current
                        DESCRIPTION
                                "UEP configuration OK."
                        ::=  {mp800mkOkTraps 3}

		-- Temperature measurement
		mp800mkTMOkTrap NOTIFICATION-TYPE
                        OBJECTS {
         mp800mkTrapParameter,
				 mp800mkTrapValue,
				 mp800mkTrapComment}
			STATUS		current
                        DESCRIPTION
                                "Temperature measurement OK."
                        ::=  {mp800mkOkTraps 4}

		-- AC voltage measurement
		mp800mkACVMOkTrap NOTIFICATION-TYPE
                        OBJECTS {
         mp800mkTrapParameter,
				 mp800mkTrapValue,
				 mp800mkTrapComment}
			STATUS		current
                        DESCRIPTION
                                "ACV measurement OK."
                        ::=  {mp800mkOkTraps 5}

		-- Battery current measurement
		mp800mkIbatMOkTrap NOTIFICATION-TYPE
                        OBJECTS {
         mp800mkTrapParameter,
				 mp800mkTrapValue,
				 mp800mkTrapComment}
			STATUS		current
                        DESCRIPTION
                                "Battery current measurement OK."
                        ::=  {mp800mkOkTraps 6}

		-- Battery voltage measurement
		mp800mkVbatMOkTrap NOTIFICATION-TYPE
                        OBJECTS {
         mp800mkTrapParameter,
				 mp800mkTrapValue,
				 mp800mkTrapComment}
			STATUS		current
                        DESCRIPTION
                                "Battery voltage measurement OK."
                        ::=  {mp800mkOkTraps 7}

		-- Battery voltage control
		mp800mkVbatChOkTrap NOTIFICATION-TYPE
                        OBJECTS {
         mp800mkTrapParameter,
				 mp800mkTrapValue,
				 mp800mkTrapComment}
			STATUS		current
                        DESCRIPTION
                                "Battery voltage changing OK."
                        ::=  {mp800mkOkTraps 8}

		-- Release device status
		mp800mkRlsDevOkTrap NOTIFICATION-TYPE
                        OBJECTS {
         mp800mkTrapParameter,
				 mp800mkTrapValue,
				 mp800mkTrapComment}
			STATUS		current
                        DESCRIPTION
                                "Release device is on."
                        ::=  {mp800mkOkTraps 9}

		-- Battery cell voltage spread
		mp800mkDVcellOkTrap NOTIFICATION-TYPE
                        OBJECTS {
         mp800mkTrapParameter,
				 mp800mkTrapValue,
				 mp800mkTrapComment}
			STATUS		current
                        DESCRIPTION
                                "Battery cell voltage spread is in range."
                        ::=  {mp800mkOkTraps 10}

		-- AC voltage
		mp800mkACVOkTrap NOTIFICATION-TYPE
                        OBJECTS {
         mp800mkTrapParameter,
				 mp800mkTrapValue,
				 mp800mkTrapComment}
			STATUS		current
                        DESCRIPTION
                                "AC voltage is in range."
                        ::=  {mp800mkOkTraps 11}

		-- Battery charge status
		mp800mkBatChargeOkTrap NOTIFICATION-TYPE
                        OBJECTS {
         mp800mkTrapParameter,
				 mp800mkTrapValue,
				 mp800mkTrapComment}
			STATUS		current
                        DESCRIPTION
                                "Battery charge status is OK."
                        ::=  {mp800mkOkTraps 12}

		-- Load current
		mp800mkIloadOkTrap NOTIFICATION-TYPE
                        OBJECTS {
         mp800mkTrapParameter,
				 mp800mkTrapValue,
				 mp800mkTrapComment}
			STATUS		current
                        DESCRIPTION
                                "Load current is in range."
                        ::=  {mp800mkOkTraps 13}

		-- Battery charge current
		mp800mkIbatChOkTrap NOTIFICATION-TYPE
                        OBJECTS {
         mp800mkTrapParameter,
				 mp800mkTrapValue,
				 mp800mkTrapComment}
			STATUS		current
                        DESCRIPTION
                                "Battery charge current is in range."
                        ::=  {mp800mkOkTraps 14}

		-- Power supply status
		mp800mkSuppOkTrap NOTIFICATION-TYPE
                        OBJECTS {
         mp800mkTrapParameter,
				 mp800mkTrapValue,
				 mp800mkTrapComment}
			STATUS		current
                        DESCRIPTION
                                "Power supply from MPs."
                        ::=  {mp800mkOkTraps 15}

		-- Battery disconnected?
		mp800mkBatConnOkTrap NOTIFICATION-TYPE
                        OBJECTS {
         mp800mkTrapParameter,
				 mp800mkTrapValue,
				 mp800mkTrapComment}
			STATUS		current
                        DESCRIPTION
                                "Battery is connected to MPs' output."
                        ::=  {mp800mkOkTraps 16}

-- mp800mk trap properties
mp800mkTrapTypes  OBJECT IDENTIFIER   ::= { eltrapGroup 10 }

    mp800mkTrapParameter OBJECT-TYPE
	SYNTAX		DisplayString
	MAX-ACCESS	read-only
	STATUS		current
	DESCRIPTION	"Parameter (V, I, T, etc...)"
	::= { mp800mkTrapTypes 1 }

    mp800mkTrapValue OBJECT-TYPE
	SYNTAX		DisplayString
	MAX-ACCESS	read-only
	STATUS		current
	DESCRIPTION	"Value (X mV, Y mA, Z grad, etc...)"
	::= { mp800mkTrapTypes 2 }

    mp800mkTrapComment OBJECT-TYPE
	SYNTAX		DisplayString
	MAX-ACCESS	read-only
	STATUS		current
	DESCRIPTION	"Comment (V is out of range [Vmin ... Vmax]!, etc...)"
	::= { mp800mkTrapTypes 3 }

---------------------------------------------------------------------------------------------------------------------------
------------------------------------------- END MP800MK Traps -------------------------------------------------------------
---------------------------------------------------------------------------------------------------------------------------

eltrapNotificationGroup NOTIFICATION-GROUP
	NOTIFICATIONS {
		mc240StreamAlarmTrap,
		mc240SyncAlarmTrap,
		mc240ss7LinkAlarmTrap,
		mc240ss7LinksetAlarmTrap,
		mc240FileAlarmTrap,
		mc240CardAlarmTrap,
		mxlDPSAlarmTrap,
		mxlTELEAlarmTrap,
		mc240UPSAlarmTrap,
		mc240SensAlarmTrap,
		dslamLinkDownTrap,
		dslamDSRateAlarmTrap,
		dslamUSRateAlarmTrap,
		ponONUAuthAlarmTrap,
		ponEthAlarmTrap,
		ponOpticalAlarmTrap,
		mc240StreamOkTrap,
		mc240SyncOkTrap,
		mc240ss7LinkOkTrap,
		mc240ss7LinksetOkTrap,
		mc240FileOkTrap,
		mc240CardOkTrap,
		mxlDPSOkTrap,
		mxlTELEOkTrap,
		mc240UPSOkTrap,
		mc240SensOkTrap,
		dslamLinkUpTrap,
		dslamDSRateOkTrap,
		dslamUSRateOkTrap,
		ponONUAuthOkTrap,
		ponEthOkTrap,
		ponOpticalOkTrap,
		dslamOverheatAlarmTrap,
		dslamVoltageAlarmTrap,
		dslamSessionAlarmTrap,
		dslamEthLinkAlarmTrap,
		dslamOverheatOkTrap,
		dslamVoltageOkTrap,
		dslamSessionOkTrap,
		dslamEthLinkOkTrap,

		mp800mkMPStatusAlarmTrap,
		mp800mkInpParmAlarmTrap,
		mp800mkUEPConfAlarmTrap,
		mp800mkTMAlarmTrap,
		mp800mkACVMAlarmTrap,
		mp800mkIbatMAlarmTrap,
		mp800mkVbatMAlarmTrap,
		mp800mkVbatChAlarmTrap,
		mp800mkRlsDevAlarmTrap,
		mp800mkDVcellAlarmTrap,
		mp800mkACVAlarmTrap,
		mp800mkBatChargeAlarmTrap,
		mp800mkIloadAlarmTrap,
		mp800mkIbatChAlarmTrap,
		mp800mkSuppAlarmTrap,
		mp800mkBatConnAlarmTrap,
		mp800mkMPStatusOkTrap,
		mp800mkInpParmOkTrap,
		mp800mkUEPConfOkTrap,
		mp800mkTMOkTrap,
		mp800mkACVMOkTrap,
		mp800mkIbatMOkTrap,
		mp800mkVbatMOkTrap,
		mp800mkVbatChOkTrap,
		mp800mkRlsDevOkTrap,
		mp800mkDVcellOkTrap,
		mp800mkACVOkTrap,
		mp800mkBatChargeOkTrap,
		mp800mkIloadOkTrap,
		mp800mkIbatChOkTrap,
		mp800mkSuppOkTrap,
		mp800mkBatConnOkTrap,

		omsOperationCommandAlarm,
		omsOperationCommandOk
		 }
	STATUS  current
	DESCRIPTION
		""
	::= { eltrapGroup 100 }

eltrapObjectGroup OBJECT-GROUP
	OBJECTS {
		mcTrapExState,
		mcTrapLParam1,
		mcTrapLParam2,
		mcTrapLParam3,
		mcTrapID,
		mcTrapDescr,
		mcTrapRestoredAlarmID,
		mcTrapSyncType,
		mcReservedFlag }
	STATUS  current
	DESCRIPTION
		""
	::= { eltrapGroup 101 }

END
