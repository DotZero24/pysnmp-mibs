ELTEX-MES-ISS-SNTP-MIB DEFINITIONS ::= BEGIN

IMPORTS
        MODULE-IDENTITY, OBJECT-TYPE, Integer32
                FROM SNMPv2-SMI
        TEXTUAL-CONVENTION
                FROM SNMPv2-TC
        eltMesIss
                FROM ELTEX-MES-ISS-MIB
        fsSntpUnicastServerEntry
                FROM FSSNTP-MIB;

eltMesIssSntpMIB MODULE-IDENTITY
        LAST-UPDATED "202012110000Z"
        ORGANIZATION "Eltex Enterprise, Ltd."
        CONTACT-INFO
                "eltex-co.ru"
        DESCRIPTION
                "MIB extensions for SNTP."
        REVISION "201908150000Z"
        DESCRIPTION "Initial revision."
        REVISION "202012110000Z"
        DESCRIPTION " Added eltMesSntpUnicastServerPriority field"
    ::= { eltMesIss 16 }

-- ----------------------
-- Textual Conventions --
-- ----------------------

NtpStratumType ::= TEXTUAL-CONVENTION
    STATUS       current
    DESCRIPTION
        "Indicates the stratum of the clock. The stratum
         defines the accuracy of a time server. Higher the
         stratum, lower the accuracy.
         0, unspecified
         1, primary reference (e.g., calibrated atomic clock,
            radio clock)
         2-255, secondary reference (via NTP)"
    SYNTAX       Integer32 (0..255)

-- --------------------------
-- Top level MIB structure --
-- --------------------------

    eltMesIssSntpObjects    OBJECT IDENTIFIER ::= { eltMesIssSntpMIB 1 }

-- --------------------
-- Groups in the MIB --
-- --------------------

    eltMesIssSntpUnicast    OBJECT IDENTIFIER ::= { eltMesIssSntpObjects 1 }


eltMesIssSntpUnicastServerTable OBJECT-TYPE
    SYNTAX      SEQUENCE OF EltMesIssSntpUnicastServerEntry
    MAX-ACCESS  not-accessible
    STATUS      current
    DESCRIPTION
        "This table augments the fsSntpUnicastServerTable table."
    ::= { eltMesIssSntpUnicast 1 }

eltMesIssSntpUnicastServerEntry OBJECT-TYPE
    SYNTAX      EltMesIssSntpUnicastServerEntry
    MAX-ACCESS  not-accessible
    STATUS      current
    DESCRIPTION
        "Each entry in the table contains necessary information
         to send SNTP request to the servers."
    AUGMENTS { fsSntpUnicastServerEntry }
    ::= { eltMesIssSntpUnicastServerTable 1 }

EltMesIssSntpUnicastServerEntry ::=
   SEQUENCE {
        eltMesIssSntpUnicastServerStratum    NtpStratumType,
        eltMesIssSntpUnicastServerPriority   Integer32
   }

eltMesIssSntpUnicastServerStratum  OBJECT-TYPE
    SYNTAX      NtpStratumType
    MAX-ACCESS  read-only
    STATUS      current
    DESCRIPTION
        "The stratum of this server. It classifies the serves in
         levels (strata), thus indicating the distance between
         this server and a reference clock."
    ::= { eltMesIssSntpUnicastServerEntry 1 }

eltMesIssSntpUnicastServerPriority OBJECT-TYPE
    SYNTAX      Integer32 (1..15)
    MAX-ACCESS  read-write
    STATUS      current
    DESCRIPTION
        "This parameter is responsible for the priority of this server
         over the rest. The priority value ranges from 1 to 15,
         with 1 being the highest priority and 15 being the lowest priority."
    ::= { eltMesIssSntpUnicastServerEntry 2 }

END
