ELTEX-MES-IP-OSPF-MTU-MIB DEFINITIONS ::= BEGIN

-- Title:      Eltex's MES Switches Private MIB
-- Version:    1.00
-- Date:       30-Aug-2013

IMPORTS
    eltMes                       FROM ELTEX-MES
    IpAddress,
    OBJECT-TYPE,
    MODULE-IDENTITY              FROM SNMPv2-SMI
    RowStatus                    FROM SNMPv2-TC;


eltMesIpOspfMtu MODULE-IDENTITY
                LAST-UPDATED "201308300000Z"
                ORGANIZATION "Eltex Enterprise Co, Ltd."
                CONTACT-INFO
                      "www.eltex.nsk.ru"
                DESCRIPTION
                      "This private MIB module defines End of Eltex private MIBs."
                REVISION "201308300000Z"
                DESCRIPTION
                      "Initial revision."
    ::= { eltMes 4 }

--
-- eltMesIpOspfMtu
--
eltIpOspfMtuTable   OBJECT-TYPE
    SYNTAX  SEQUENCE OF EltIpOspfMtuEntry
    MAX-ACCESS  not-accessible
    STATUS  current
    DESCRIPTION
        ""
    ::= { eltMesIpOspfMtu 1 }

eltIpOspfMtuEntry   OBJECT-TYPE
    SYNTAX  EltIpOspfMtuEntry
    MAX-ACCESS  not-accessible
    STATUS  current
    DESCRIPTION
        ""
    INDEX { ipAddr }
    ::= { eltIpOspfMtuTable 1 }


EltIpOspfMtuEntry ::= SEQUENCE {
    ipAddr               IpAddress,
    ipOspfMtu            INTEGER,
    ipOspfMtuRowStatus   RowStatus
}

ipAddr OBJECT-TYPE
    SYNTAX     IpAddress
    MAX-ACCESS read-only
    STATUS     deprecated
    DESCRIPTION
           ""
    ::= { eltIpOspfMtuEntry 1 }

ipOspfMtu OBJECT-TYPE
    SYNTAX     INTEGER (128..10218)
    MAX-ACCESS read-write
    STATUS     deprecated
    DESCRIPTION
           ""
    ::= { eltIpOspfMtuEntry 2 }

ipOspfMtuRowStatus OBJECT-TYPE
    SYNTAX      RowStatus
    MAX-ACCESS  read-create
    STATUS      current
    DESCRIPTION
       "The status of the row.

        The writable columns in a row can not be changed if the row
        is active. All columns MUST have a valid value before a row
        can be activated.
       "
    ::= { eltIpOspfMtuEntry 3 }

END
