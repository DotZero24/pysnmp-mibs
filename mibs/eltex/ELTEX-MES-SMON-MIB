ELTEX-MES-SMON-MIB DEFINITIONS ::= BEGIN

-- Title:                Eltex MES Private SMON MIB
-- Version:              1.0
-- Date:                 10-Feb-2016

IMPORTS
    eltMes                                                  FROM ELTEX-MES
    OBJECT-TYPE, MODULE-IDENTITY                            FROM SNMPv2-SMI
    TruthValue                                              FROM SNMPv2-TC
    dot1dBasePort                                           FROM BRIDGE-MIB
    VlanId                                                  FROM Q-BRIDGE-MIB
    RowStatus, TEXTUAL-CONVENTION                           FROM SNMPv2-TC;

EltPortCopyRemoteDirectionType ::= TEXTUAL-CONVENTION
    STATUS current
    DESCRIPTION    "copy remote direction type:
                    1- Rx
                    2- Tx"
    SYNTAX INTEGER {
        eltPortCopyRemoteRx(1),
        eltPortCopyRemoteTx(2)
	}

eltMesSmon MODULE-IDENTITY
                LAST-UPDATED "201602100000Z"
                ORGANIZATION "Eltex Enterprise, Ltd."
                CONTACT-INFO
                      "www.eltex.nsk.ru"
                DESCRIPTION
                      "This private MIB module defines SMON private MIBs."
                REVISION "201602100000Z"
                DESCRIPTION
                      "Initial revision."
        ::= { eltMes 84 }

eltPortCopyRemoteTable OBJECT-TYPE
    SYNTAX  SEQUENCE OF EltPortCopyRemoteEntry
    MAX-ACCESS  not-accessible
    STATUS  current
    DESCRIPTION
        "A supplementing table for eltPortCopyRemoteTable."
    ::= { eltMesSmon 1 }

eltPortCopyRemoteEntry OBJECT-TYPE
    SYNTAX  EltPortCopyRemoteEntry
    MAX-ACCESS  not-accessible
    STATUS  current
    DESCRIPTION
        "Each entry specifies vlan tag and user priority added
        by analyzer to a mirrored Rx/Tx packets."
    INDEX   { eltPortCopyRemoteDirection }
    ::= { eltPortCopyRemoteTable 1 }

EltPortCopyRemoteEntry ::=
    SEQUENCE {
        eltPortCopyRemoteDirection   EltPortCopyRemoteDirectionType,
        eltPortCopyRemoteVlan        VlanId,
        eltPortCopyRemotePrio        INTEGER,
        eltPortCopyRemoteStatus      RowStatus
    }

eltPortCopyRemoteDirection  OBJECT-TYPE
      SYNTAX                EltPortCopyRemoteDirectionType
      MAX-ACCESS            not-accessible
      STATUS                current
      DESCRIPTION "This field defines a direction"
      ::= { eltPortCopyRemoteEntry 1 }

eltPortCopyRemoteVlan  OBJECT-TYPE
      SYNTAX                VlanId
      MAX-ACCESS            read-write
      STATUS                current
      DESCRIPTION "This field defines an RSPAN VLAN id"
      ::= { eltPortCopyRemoteEntry 2 }

eltPortCopyRemotePrio  OBJECT-TYPE
      SYNTAX                INTEGER (0..7)
      MAX-ACCESS            read-write
      STATUS                current
      DESCRIPTION "This field defines an RSPAN user priority"
      DEFVAL { 0 }
      ::= { eltPortCopyRemoteEntry 3 }

eltPortCopyRemoteStatus  OBJECT-TYPE
      SYNTAX                RowStatus
      MAX-ACCESS            read-create
      STATUS                current
      DESCRIPTION "This field defines a row status"
      ::= { eltPortCopyRemoteEntry 4 }

END
