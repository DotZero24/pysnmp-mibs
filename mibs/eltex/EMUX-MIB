EMUX-MIB DEFINITIONS ::= BEGIN
	IMPORTS
		enterprises,
		MODULE-IDENTITY,
		IpAddress,
		Counter32,
		Counter64,
		Integer32,
		Gauge32,
		OBJECT-TYPE,
		NOTIFICATION-TYPE               FROM SNMPv2-SMI
		ifIndex				FROM IF-MIB
		DateAndTime,
		DisplayString,
		MacAddress,
		TEXTUAL-CONVENTION		FROM SNMPv2-TC
		Float		                FROM UCD-SNMP-MIB
		OBJECT-GROUP,
		MODULE-COMPLIANCE,
		NOTIFICATION-GROUP		FROM SNMPv2-CONF
		dot1dBridge			FROM BRIDGE-MIB
		usmStats			FROM SNMP-USER-BASED-SM-MIB
		rstpMIB				FROM RSTP-MIB;

	nsc MODULE-IDENTITY
		LAST-UPDATED "201807310000Z"
		ORGANIZATION "NSC Communications Siberia Ltd"
		CONTACT-INFO
				"NSC, Novosibirsk, Vokzalnaya magistral 16-312
				tel. +7(383)363-34-42
				www.nsc-com.com"
		DESCRIPTION "The MIB module to describe objects for network devices."
		REVISION "201807310000Z"
		DESCRIPTION "Add new params and correction of typos"
		REVISION "201801180000Z"
		DESCRIPTION "Add missing counters and parameters in E1 statistics"
		REVISION "201706010000Z"
		DESCRIPTION "Correct to 9.4SR39"
		REVISION "201703020000Z"
		DESCRIPTION "Correct to 9.4SR37"
		REVISION "201603250000Z"
		DESCRIPTION "Correct to 9.4SR31"
		REVISION "201506030000Z"
		DESCRIPTION "Correct to 9.4SR26"
		REVISION "201501150000Z"
		DESCRIPTION "Fixing bugs in mib"
		REVISION "201209060000Z"
		DESCRIPTION "Initial revision"
		::=	{ enterprises 42926 }

	emux	OBJECT IDENTIFIER ::=	{ nsc 2 }

	general OBJECT IDENTIFIER ::=	{emux 3 }
	basic OBJECT IDENTIFIER ::=	{general 1 }

        muxConformance OBJECT IDENTIFIER ::= { emux 30 }
	muxGroups OBJECT IDENTIFIER ::= { muxConformance 1 }
	muxCompliances OBJECT IDENTIFIER ::= { muxConformance 2 }

	TimeSlotMask ::= TEXTUAL-CONVENTION
    DISPLAY-HINT "1x:"
    STATUS       current
    DESCRIPTION
            "Represents time slot mask"
    SYNTAX       OCTET STRING

	E1Status ::= TEXTUAL-CONVENTION
	STATUS         current
	DESCRIPTION    "E1 channel hardware status"
	SYNTAX         BITS   { 		nos(0),		ais(1),		azs(2),		los(3),		rai(4),		prbserr(5),		testerr(6),		loopdet(7),		txlock(8),		codeerr(9), fastpulseerr(10), rarepulseerr(11), mfaserr(12), rcrc4err(13), crc4err(14), ok(16) 	}


	CRC4Status ::= TEXTUAL-CONVENTION
	STATUS         current
	DESCRIPTION    "CRC4 channel hardware status"
	SYNTAX         BITS { check(0), send(1), reicheck(2), reisend(3) }


	sysHWVer   OBJECT-TYPE
	SYNTAX  DisplayString
	MAX-ACCESS  read-only
	STATUS current
	DESCRIPTION "Device Hardaware version in form: ident.hw1_revision rev hw2_revision"
	::= { basic 1 }


	sysOSVer   OBJECT-TYPE
	SYNTAX  DisplayString
	MAX-ACCESS  read-only
	STATUS current
	DESCRIPTION "OS Version in form: OS_NAME version (build date)"
	::= { basic 2 }

	hwDescr   OBJECT-TYPE
	SYNTAX  DisplayString
	MAX-ACCESS  read-only
	STATUS current
	DESCRIPTION "Hardware name"
	::= { basic 3 }

	manContact   OBJECT-TYPE
	SYNTAX  DisplayString
	MAX-ACCESS  read-write
	STATUS current
	DESCRIPTION "Manufacturer contacts"
	::= { basic 4 }

	sysDevname   OBJECT-TYPE
	SYNTAX  DisplayString
	MAX-ACCESS  read-only
	STATUS current
	DESCRIPTION "Name of device"
	::= { basic 5 }

	devLocation   OBJECT-TYPE
	SYNTAX  DisplayString
	MAX-ACCESS  read-only
	STATUS current
	DESCRIPTION "Device location"
	::= { basic 6 }

	sysReset   OBJECT-TYPE
	SYNTAX  DisplayString
	MAX-ACCESS  read-write
	STATUS current
	DESCRIPTION "Write here special string to reset device"
	::= { basic 7 }

	sysID   OBJECT-TYPE
	SYNTAX  DisplayString
	MAX-ACCESS  read-only
	STATUS current
	DESCRIPTION "Unique device identifier"
	::= { basic 8 }

	sysDateTime   OBJECT-TYPE
	SYNTAX  DisplayString
	MAX-ACCESS  read-write
	STATUS current
	DESCRIPTION "Device local time"
	::= { basic 9 }

	sysLicenseValid   OBJECT-TYPE
	SYNTAX  INTEGER { valid(1), invalid(2) }
	MAX-ACCESS  read-only
	STATUS current
	DESCRIPTION "Check for device licensing"
	::= { basic 10 }

	sysSaveConfig   OBJECT-TYPE
	SYNTAX DisplayString
	MAX-ACCESS read-write
	STATUS current
	DESCRIPTION "Save configuration to flash"
	::= { basic 11 }

	sysUpdate   OBJECT-TYPE
	SYNTAX DisplayString
	MAX-ACCESS read-write
	STATUS current
	DESCRIPTION "Update system OS"
	::= { basic 12 }

	sysVendor   OBJECT-TYPE
	SYNTAX  DisplayString
	MAX-ACCESS  read-only
	STATUS current
	DESCRIPTION "Manufacturer information"
	::= { basic 13 }

	oldSysID   OBJECT-TYPE
	SYNTAX  DisplayString
	MAX-ACCESS  read-only
	STATUS current
	DESCRIPTION "Previous device identifier"
	::= { basic 14 }

	muxBaseGroup OBJECT-GROUP
	OBJECTS { 	sysHWVer,
				sysOSVer,
				hwDescr,
				manContact,
				sysDevname,
				devLocation,
				sysReset,
				sysID,
				sysDateTime,
				sysLicenseValid,
				sysSaveConfig,
				sysUpdate,
				sysVendor,
				oldSysID
			}
	STATUS current
	DESCRIPTION
		"A collection of objects providing minimal information about device revision"
--	::= { basic 13 }
	::= { muxGroups 1 }


	e1	OBJECT IDENTIFIER ::=	{emux 18 }
	e1Number   OBJECT-TYPE
	SYNTAX  Integer32
	MAX-ACCESS  read-only
	STATUS current
	DESCRIPTION "Number of E1 ports"
	::= { e1 1 }

    e1ConfigTable					OBJECT-TYPE
	SYNTAX					SEQUENCE OF E1ConfigTableEntrySeq
	MAX-ACCESS					not-accessible
	STATUS					current
	DESCRIPTION				"A list of E1 channels"
	::= { e1 6 }


  	E1ConfigTableEntrySeq ::=
    SEQUENCE {
			e1ChIndex 	Integer32,
			e1ChStatus	DisplayString,
			e1ChLinkStatus INTEGER,
			e1ChLinkEnable INTEGER,
			e1ChResetConfig DisplayString,
			e1LocalLoopback   INTEGER,
			e1RecvUnframed   INTEGER,
			e1SendType   	INTEGER,
			e1SyncSource   	INTEGER,
			e1TxSpeed   	Integer32,
			e1TestFrameRTT	Gauge32,
			e1RecvStatus   	E1Status,
			e1SendStatus   E1Status,
			e1RXSpeed   	Integer32,
			e1LongLine	INTEGER,
			e1SignalLevel DisplayString,
			e1NoLogEvents  	E1Status,
			e1CRC4  	CRC4Status,
			e1PRBSCheck   INTEGER
           }

	e1ConfigTableEntry			OBJECT-TYPE
	SYNTAX					E1ConfigTableEntrySeq
	MAX-ACCESS					not-accessible
	STATUS					current
	DESCRIPTION				"A list of E1 channels"
	INDEX   { e1ChIndex }
	::= { e1ConfigTable 1}

	e1ChIndex   OBJECT-TYPE
	SYNTAX  Integer32(0..128)
--	MAX-ACCESS  read-only
	MAX-ACCESS					not-accessible
	STATUS current
	DESCRIPTION "Index of E1 connection"
	::= { e1ConfigTableEntry 1 }

	e1ChStatus   OBJECT-TYPE
	SYNTAX  DisplayString
	MAX-ACCESS  read-only
	STATUS current
	DESCRIPTION "String status of E1 port"
	::= { e1ConfigTableEntry 2 }

	e1ChLinkStatus   OBJECT-TYPE
	SYNTAX  INTEGER { up(1),down(2) }
	MAX-ACCESS  read-only
	STATUS current
	DESCRIPTION "E1 port status"
	::= { e1ConfigTableEntry 3 }

	e1ChLinkEnable   OBJECT-TYPE
	SYNTAX  INTEGER { enabled(1),disabled(2) }
	MAX-ACCESS  read-write
	STATUS current
	DESCRIPTION "Port admin state (phisical)"
	::= { e1ConfigTableEntry 4 }

	e1ChResetConfig   OBJECT-TYPE
	SYNTAX  DisplayString
	MAX-ACCESS  read-write
	STATUS current
	DESCRIPTION "Write special string here to reset port configuration"
	::= { e1ConfigTableEntry 5 }

	e1LocalLoopback   OBJECT-TYPE
	SYNTAX  INTEGER { enabled(1), disabled(2) }
	MAX-ACCESS  read-write
	STATUS current
	DESCRIPTION "TDMoP->E1->TDMoP loopback"
	::= { e1ConfigTableEntry 7 }

	e1RecvUnframed   OBJECT-TYPE
	SYNTAX  INTEGER { enabled(1), disabled(2) }
	MAX-ACCESS  read-write
	STATUS current
	DESCRIPTION "enabled - rx in G.703, disabled - rx in G.704"
	::= { e1ConfigTableEntry 8 }

	e1SendType   OBJECT-TYPE
	SYNTAX  INTEGER { ais(0), azs(1), prbs(2), testFrames(3), tdmop(4) }
	MAX-ACCESS  read-write
	STATUS current
	DESCRIPTION "The type of data sent to the line"
	::= { e1ConfigTableEntry 10 }

	e1SyncSource   OBJECT-TYPE
	SYNTAX  INTEGER { restore(-1) }
	MAX-ACCESS  read-write
	STATUS current
	DESCRIPTION "Stream number E1, synchronization source. -1 - restore the synchronization"
	::= { e1ConfigTableEntry 11 }

	e1TxSpeed   OBJECT-TYPE
	SYNTAX  Integer32
	UNITS	"ppb"
	MAX-ACCESS  read-write
	STATUS current
	DESCRIPTION "The deviation of the frequency of the outgoing stream from the internal"
	::= { e1ConfigTableEntry 15 }

	e1TestFrameRTT   OBJECT-TYPE
	SYNTAX  Gauge32
	UNITS "UI"
	MAX-ACCESS  read-only
	STATUS current
	DESCRIPTION "Round trip time. Only if e1SendType = testFrames (G.704)"
	::= { e1ConfigTableEntry 16 }

	e1RecvStatus   OBJECT-TYPE
	SYNTAX  E1Status
	MAX-ACCESS  read-only
	STATUS current
	DESCRIPTION "Hardware status of the receiver of the stream E1"
	::= { e1ConfigTableEntry 17 }

	e1SendStatus   OBJECT-TYPE
	SYNTAX  E1Status
	MAX-ACCESS  read-only
	STATUS current
	DESCRIPTION "Hardware status of the transmitter of the stream E1"
	::= { e1ConfigTableEntry 18 }

	e1RXSpeed   OBJECT-TYPE
	SYNTAX  Integer32
	UNITS	"ppb"
	MAX-ACCESS  read-only
	STATUS current
	DESCRIPTION "The deviation of the frequency of the incoming stream from the internal"
	::= { e1ConfigTableEntry 21 }

	e1LongLine   OBJECT-TYPE
	SYNTAX  INTEGER { enabled(1), disabled(2) }
	MAX-ACCESS  read-write
	STATUS current
	DESCRIPTION "Long line mode for e1 reciever"
	::= { e1ConfigTableEntry 22 }

	e1SignalLevel   OBJECT-TYPE
	SYNTAX  DisplayString
	MAX-ACCESS  read-only
	STATUS current
	DESCRIPTION "Level of E1 signal, when long line option is enabled"
	::= { e1ConfigTableEntry 23 }

	e1NoLogEvents OBJECT-TYPE
	SYNTAX  E1Status
	MAX-ACCESS  read-write
	STATUS current
	DESCRIPTION "Disable logging of selected events"
	::= { e1ConfigTableEntry 24 }

	e1CRC4 OBJECT-TYPE
	SYNTAX  CRC4Status
	MAX-ACCESS  read-write
	STATUS current
	DESCRIPTION "Use cyclic redundancy check in multiframe"
	::= { e1ConfigTableEntry 25 }

	e1PRBSCheck   OBJECT-TYPE
	SYNTAX  INTEGER { enabled(1), disabled(2) }
	MAX-ACCESS  read-write
	STATUS current
	DESCRIPTION "Checking the PRBS-31 sequence"
	::= { e1ConfigTableEntry 26 }

	e1Group OBJECT-GROUP
	OBJECTS { 		e1Number,
--				e1ChIndex,
				e1ChStatus,
				e1ChLinkStatus,
				e1ChLinkEnable,
				e1ChResetConfig,
				e1LocalLoopback,
				e1RecvUnframed,
				e1SendType,
				e1SyncSource,
				e1TxSpeed,
				e1TestFrameRTT,
				e1RecvStatus,
				e1SendStatus,
				e1RXSpeed,
				e1LongLine,
				e1SignalLevel,
				e1NoLogEvents,
				e1CRC4,
				e1PRBSCheck
			}
	STATUS current
	DESCRIPTION
		"A collection of objects providing minimal information about e1 interfaces"
--	::= { e1 13 }
	::= { muxGroups 2 }


	tdmConfigTable					OBJECT-TYPE
	SYNTAX					SEQUENCE OF TDMChEntrySeq
	MAX-ACCESS					not-accessible
	STATUS					current
	DESCRIPTION				"A list of E1 channels"
	::= { e1 7 }


  	TDMChEntrySeq ::=
    SEQUENCE {
			tdmChIndex Integer32,
			tdmStatus DisplayString,
			tdmLinkStatus INTEGER,
			tdmAdminStatus INTEGER,
			tdmResetConfig DisplayString,
			tdmFrameSize Integer32,
			tdmJBSize Integer32,
			tdmCurrentTimeout Integer32,
			tdmMode INTEGER,
			tdmHasData INTEGER,
			tdmCurrentJBSize Integer32,
			tdmLocalTSMask TimeSlotMask,
			tdmRemoteTSMask TimeSlotMask,
			tdmVLANID Integer32,
			tdmVLANPri Integer32,
			tdmUseIP INTEGER,
			tdmLostRequest    INTEGER,
			tdmRedirectedIP   IpAddress,
			tdmRedirectedMAC   MacAddress,
			tdmRedirectedChannel   Integer32,
			tdmOriginalIP   IpAddress,
			tdmOriginalMAC   MacAddress,
			tdmOriginalChannel   Integer32,
			tdmRemoteLoop   INTEGER,
			tdmTos   Integer32,
			tdmSpeedRegualator   DisplayString,
			tdmSpeed   Integer32,
			tdmConfigured   INTEGER,
			tdmUseConstSpeed   INTEGER ,
			tdmMaxTimeout   Integer32,
			tdmUsedTimeSlots   Integer32,
			tdmCompression   INTEGER,
			tdmKeyFrameInterval   Integer32,
			tdmDescription   DisplayString,
			tdmDoubleSend   Integer32,
			tdmConstSpeed Integer32,
			tdmInterpMode INTEGER,
			tdmProtocol INTEGER,
			tdmDSCP DisplayString
           }

	tdmConfigTableEntry 			OBJECT-TYPE
	SYNTAX					TDMChEntrySeq
	MAX-ACCESS					not-accessible
	STATUS					current
	DESCRIPTION				"A list of TDM channels"
	INDEX   { tdmChIndex }
	::= { tdmConfigTable 1}

	tdmChIndex   OBJECT-TYPE
	SYNTAX  Integer32(0..128)
--	MAX-ACCESS  read-only
	MAX-ACCESS					not-accessible
	STATUS current
	DESCRIPTION "Index of TDM connection"
	::= { tdmConfigTableEntry 1 }



	tdmStatus   OBJECT-TYPE
	SYNTAX  DisplayString
	MAX-ACCESS  read-only
	STATUS current
	DESCRIPTION "Current connection status"
	::= { tdmConfigTableEntry 2 }

	tdmLinkStatus   OBJECT-TYPE
	SYNTAX  INTEGER { up(1), down(2) }
	MAX-ACCESS  read-only
	STATUS current
	DESCRIPTION "Current link status"
	::= { tdmConfigTableEntry 3 }


	tdmAdminStatus   OBJECT-TYPE
	SYNTAX  INTEGER { listen(0), connect(1), blocked(2),alwaysSend(3) }
	MAX-ACCESS  read-write
	STATUS current
	DESCRIPTION "TDMoP transmit and recv control"
	::= { tdmConfigTableEntry 5 }

	tdmResetConfig   OBJECT-TYPE
	SYNTAX  DisplayString
	MAX-ACCESS  read-write
	STATUS current
	DESCRIPTION "Write reset to reset channel configuration"
	::= { tdmConfigTableEntry 7 }

	tdmFrameSize   OBJECT-TYPE
	SYNTAX  Integer32
	UNITS	"1/2ms"
	MAX-ACCESS  read-write
	STATUS current
	DESCRIPTION "Transmit frame size, must be equal for local and remote side"
	::= { tdmConfigTableEntry 8 }

	tdmJBSize   OBJECT-TYPE
	SYNTAX  Integer32
	UNITS "ms"
	MAX-ACCESS  read-write
	STATUS current
	DESCRIPTION "Admin Jitter Buffer size"
	::= { tdmConfigTableEntry 9 }

	tdmCurrentTimeout   OBJECT-TYPE
	SYNTAX  Integer32
	UNITS "ms"
	MAX-ACCESS  read-only
	STATUS current
	DESCRIPTION "Current no-frames recvd time"
	::= { tdmConfigTableEntry 10 }

	tdmMode   OBJECT-TYPE
	SYNTAX  INTEGER { down(0), waitingSync(1),accumulating(2),working(3) }
	MAX-ACCESS  read-only
	STATUS current
	DESCRIPTION "Current TDMoP recv status"
	::= { tdmConfigTableEntry 11 }

	tdmHasData   OBJECT-TYPE
	SYNTAX  INTEGER { ok(1), nodata(2) }
	MAX-ACCESS  read-only
	STATUS current
	DESCRIPTION "nodata when no valid frames detected"
	::= { tdmConfigTableEntry 12 }

	tdmCurrentJBSize   OBJECT-TYPE
	SYNTAX  Integer32
	UNITS "us"
	MAX-ACCESS  read-only
	STATUS current
	DESCRIPTION "Current Jitter buffre size"
	::= { tdmConfigTableEntry 13 }

	tdmLocalTSMask   OBJECT-TYPE
	SYNTAX  TimeSlotMask
	MAX-ACCESS  read-only
	STATUS current
	DESCRIPTION "each bit is channel"
	::= { tdmConfigTableEntry 14 }


	tdmRemoteTSMask   OBJECT-TYPE
	SYNTAX  TimeSlotMask
	MAX-ACCESS  read-only
	STATUS current
	DESCRIPTION "each bit is channel"
	::= { tdmConfigTableEntry 15 }

	tdmVLANID   OBJECT-TYPE
	SYNTAX  Integer32
	MAX-ACCESS  read-write
	STATUS current
	DESCRIPTION "Transmitter VLAN ID"
	::= { tdmConfigTableEntry 16 }

	tdmVLANPri   OBJECT-TYPE
	SYNTAX  Integer32
	MAX-ACCESS  read-write
	STATUS current
	DESCRIPTION "Transmitter VLAN Priority"
	::= { tdmConfigTableEntry 17 }


	tdmUseIP   OBJECT-TYPE
	SYNTAX  INTEGER { use(1), dontuse(2) }
	MAX-ACCESS  read-write
	STATUS current
	DESCRIPTION "Use - send over UDP/IP, dontuse - over proprietary protocol id over ethernet"
	::= { tdmConfigTableEntry 18 }


	tdmLostRequest   OBJECT-TYPE
	SYNTAX  INTEGER { request(1), ignore(2) }
	MAX-ACCESS  read-write
	STATUS current
	DESCRIPTION "Request lost TDMoP frame, when lost detected"
	::= { tdmConfigTableEntry 19 }

	tdmRedirectedIP   OBJECT-TYPE
	SYNTAX  IpAddress
	MAX-ACCESS  read-only
	STATUS current
	DESCRIPTION "IP, send by remote side, when connection was requested"
	::= { tdmConfigTableEntry 20 }

	tdmRedirectedMAC   OBJECT-TYPE
	SYNTAX  MacAddress
	MAX-ACCESS  read-only
	STATUS current
	DESCRIPTION "Redirected IP resolved MAC"
	::= { tdmConfigTableEntry 21 }

	tdmRedirectedChannel   OBJECT-TYPE
	SYNTAX  Integer32
	MAX-ACCESS  read-only
	STATUS current
	DESCRIPTION "Remote side redirection channel"
	::= { tdmConfigTableEntry 22 }

	tdmOriginalIP   OBJECT-TYPE
	SYNTAX  IpAddress
	MAX-ACCESS  read-write
	STATUS current
	DESCRIPTION "Admin set remote IP"
	::= { tdmConfigTableEntry 23 }

	tdmOriginalMAC   OBJECT-TYPE
	SYNTAX  MacAddress
	MAX-ACCESS  read-write
	STATUS current
	DESCRIPTION "Admin set remote MAC"
	::= { tdmConfigTableEntry 24 }

	tdmOriginalChannel   OBJECT-TYPE
	SYNTAX  Integer32
	MAX-ACCESS  read-write
	STATUS current
	DESCRIPTION "Admin set remote channel"
	::= { tdmConfigTableEntry 25 }

	tdmRemoteLoop   OBJECT-TYPE
	SYNTAX  INTEGER { enabled(1),disabled(2)}
	MAX-ACCESS  read-write
	STATUS current
	DESCRIPTION "Loopback data, recvd from E1 (E1->TDMoP->E1)"
	::= { tdmConfigTableEntry 28 }

	tdmTos   OBJECT-TYPE
	SYNTAX  Integer32
	MAX-ACCESS  read-write
	STATUS current
	DESCRIPTION "IP ToS"
	::= { tdmConfigTableEntry 29 }

	tdmSpeedRegualator   OBJECT-TYPE
	SYNTAX  DisplayString
	MAX-ACCESS  read-write
	STATUS current
	DESCRIPTION "PID"
	::= { tdmConfigTableEntry 30 }

	tdmSpeed   OBJECT-TYPE
	SYNTAX  Integer32
	UNITS	"ppb"
	MAX-ACCESS  read-write
	STATUS current
	DESCRIPTION "E1 Transmitter freq deviation"
	::= { tdmConfigTableEntry 31 }

	tdmConfigured   OBJECT-TYPE
	SYNTAX  INTEGER { configured(1), notConfigured(2) }
	MAX-ACCESS  read-write
	STATUS current
	DESCRIPTION "Channel is configured"
	::= { tdmConfigTableEntry 32 }

	tdmUseConstSpeed   OBJECT-TYPE
	SYNTAX  INTEGER { const(1), restored(2) }
	MAX-ACCESS  read-write
	STATUS current
	DESCRIPTION "For debug purpose only, disable algorithmical contol of freq, use tdmConstSpeed value"
	::= { tdmConfigTableEntry 33 }

	tdmMaxTimeout   OBJECT-TYPE
	SYNTAX  Integer32
	UNITS "ms"
	MAX-ACCESS  read-write
	STATUS current
	DESCRIPTION "Admin set maximum no-data timeout"
	::= { tdmConfigTableEntry 34 }

	tdmUsedTimeSlots   OBJECT-TYPE
	SYNTAX  Integer32
	MAX-ACCESS  read-only
	STATUS current
	DESCRIPTION "Number of current modified channels in local E1 stream"
	::= { tdmConfigTableEntry 35 }

	tdmCompression   OBJECT-TYPE
	SYNTAX  INTEGER { enabled(1), disabled(2) }
	MAX-ACCESS  read-write
	STATUS current
	DESCRIPTION "Admin dynamic lossless compression (do not transmit unmodified time-slots)"
	::= { tdmConfigTableEntry 36 }

	tdmKeyFrameInterval   OBJECT-TYPE
	SYNTAX  Integer32
	MAX-ACCESS  read-write
	STATUS current
	DESCRIPTION "Period in TDMoP frames, for sending all timeslots. Valid when compression is enabled."
	::= { tdmConfigTableEntry 37 }

	tdmDescription   OBJECT-TYPE
	SYNTAX  DisplayString
	MAX-ACCESS  read-write
	STATUS current
	DESCRIPTION "User desription of channel"
	::= { tdmConfigTableEntry 38 }


	tdmDoubleSend   OBJECT-TYPE
	SYNTAX  Integer32
	UNITS "frames"
	MAX-ACCESS  read-write
	STATUS current
	DESCRIPTION "-1 - never. 0..63 - duplicate TDMoP Frames on transmit delay"
	::= { tdmConfigTableEntry 39 }


	tdmConstSpeed OBJECT-TYPE
	SYNTAX Integer32
	UNITS "ppb"
	MAX-ACCESS read-write
	STATUS current
	DESCRIPTION "Const E1 freq deviation. For debug purpose only"
	::= {tdmConfigTableEntry 40 }

	tdmInterpMode   OBJECT-TYPE
	SYNTAX  INTEGER { prevdata(0), ais(1) }
	MAX-ACCESS  read-write
	STATUS current
	DESCRIPTION "Data to send, when there is no E1 stream data"
	::= { tdmConfigTableEntry 41 }

	tdmProtocol   OBJECT-TYPE
	SYNTAX  INTEGER { tdmop(0), satop(1), cesopsn(2) }
	MAX-ACCESS  read-write
	STATUS current
	DESCRIPTION "Transmission protocol for virtual connection (TDMoP, SATOP, CESoPSN)"
	::= { tdmConfigTableEntry 42 }

	tdmDSCP   OBJECT-TYPE
	SYNTAX  DisplayString
	MAX-ACCESS  read-write
	STATUS current
	DESCRIPTION "IP DSCP (0-63,af[1..4][1..3],cs[1..7],default,ef)"
	::= { tdmConfigTableEntry 43 }

	tdmGroup OBJECT-GROUP
	OBJECTS {
--        tdmChIndex,
	tdmStatus,
	tdmLinkStatus,
	tdmAdminStatus,
	tdmResetConfig,
	tdmFrameSize,
	tdmJBSize,
	tdmCurrentTimeout,
	tdmMode,
	tdmHasData,
	tdmCurrentJBSize,
	tdmLocalTSMask,
	tdmRemoteTSMask,
	tdmVLANID,
	tdmVLANPri,
	tdmUseIP,
	tdmLostRequest,
	tdmRedirectedIP,
	tdmRedirectedMAC,
	tdmRedirectedChannel,
	tdmOriginalIP,
	tdmOriginalMAC,
	tdmOriginalChannel,
	tdmRemoteLoop,
	tdmTos,
	tdmSpeedRegualator,
	tdmSpeed,
	tdmConfigured,
	tdmUseConstSpeed,
	tdmMaxTimeout,
	tdmUsedTimeSlots,
	tdmCompression,
	tdmKeyFrameInterval,
	tdmDescription,
	tdmDoubleSend,
	tdmConstSpeed,
	tdmInterpMode,
	tdmProtocol,
	tdmDSCP
	}
	STATUS current
	DESCRIPTION
	"A collection of objects providing minimal information about tdm mappings"
--	::= { e1 14 }
	::= { muxGroups 3 }

	E1StatistcsEntry ::=
    SEQUENCE {
			e1StChIndex 	Integer32,
			e1rxOkCnt		Counter32,
			e1rxNOS			Counter32,
			e1rxAIS			Counter32,
			e1rxAZS			Counter32,
			e1rxLOS			Counter32,
			e1rxRAI			Counter32,
			e1rxPRBS			Counter32,
			e1rxTest			Counter32,
			e1rxCodeErr			Counter32,
			e1rxRareErr			Counter32,
			e1rxFastErr			Counter32,
			e1rxFDev			Integer32,
			e1rxCRC4			Counter64,
			e1rxCRC4Sec			Counter32,
			e1rxCRC4Rem			Counter32,
			e1rxMfAS			Counter32,
			e1txOkCnt		Counter32,
			e1txNOS			Counter32,
			e1txAIS			Counter32,
			e1txAZS			Counter32,
			e1txLOS			Counter32,
			e1txRAI			Counter32,
			e1txPRBS			Counter32,
			e1txLock			Counter32,
			e1Start			DateAndTime,
			e1Finish			DateAndTime,
			e1Total			Counter32,
			e1txFDev		Integer32,
			e1txCRC4Sec		Counter32,
			e1txCRC4Rem		Counter32,
			e1txMfAS		Counter32
           }

	e1StatisticsTable					OBJECT-TYPE
	SYNTAX					SEQUENCE OF E1StatistcsEntry
	MAX-ACCESS					not-accessible
	STATUS					current
	DESCRIPTION				"A list of E1 channels"
	::= { e1 8 }




	e1StatisticsTableEntry			OBJECT-TYPE
	SYNTAX					E1StatistcsEntry
	MAX-ACCESS					not-accessible
	STATUS					current
	DESCRIPTION				"A list of E1 statistics"
	INDEX   { e1StChIndex }
	::= { e1StatisticsTable 1}

	e1StChIndex   OBJECT-TYPE
	SYNTAX  Integer32(0..128)
	MAX-ACCESS  not-accessible
	STATUS current
	DESCRIPTION "Channel number"
	::= { e1StatisticsTableEntry 1 }


	e1rxOkCnt   OBJECT-TYPE
	SYNTAX  Counter32
	UNITS "s"
	MAX-ACCESS  read-only
	STATUS current
	DESCRIPTION "No errors detected"
	::= { e1StatisticsTableEntry 2 }


	e1rxNOS   OBJECT-TYPE
	SYNTAX  Counter32
	UNITS "s"
	MAX-ACCESS  read-only
	STATUS current
	DESCRIPTION "No signal detected"
	::= { e1StatisticsTableEntry 3 }

	e1rxAIS   OBJECT-TYPE
	SYNTAX  Counter32
	UNITS "s"
	MAX-ACCESS  read-only
	STATUS current
	DESCRIPTION "Alarm Indication Signal"
	::= { e1StatisticsTableEntry 4 }

	e1rxAZS   OBJECT-TYPE
	SYNTAX  Counter32
	UNITS "s"
	MAX-ACCESS  read-only
	STATUS current
	DESCRIPTION "All Zeros Signal"
	::= { e1StatisticsTableEntry 5 }

	e1rxLOS   OBJECT-TYPE
	SYNTAX  Counter32
	UNITS "s"
	MAX-ACCESS  read-only
	STATUS current
	DESCRIPTION "Loss of frame"
	::= { e1StatisticsTableEntry 6 }

	e1rxRAI   OBJECT-TYPE
	SYNTAX  Counter32
	UNITS "s"
	MAX-ACCESS  read-only
	STATUS current
	DESCRIPTION "Remote alarm indication"
	::= { e1StatisticsTableEntry 7 }

	e1rxPRBS   OBJECT-TYPE
	SYNTAX  Counter32
	UNITS "s"
	MAX-ACCESS  read-only
	STATUS current
	DESCRIPTION "PRBS errors detected, valid only in PRBS test/PRBS check mode"
	::= { e1StatisticsTableEntry 8 }

	e1rxTest   OBJECT-TYPE
	SYNTAX  Counter32
	UNITS "s"
	MAX-ACCESS  read-only
	STATUS current
	DESCRIPTION "Test frames errors, valid only in TestFrames mode"
	::= { e1StatisticsTableEntry 9 }

	e1rxCodeErr   OBJECT-TYPE
	SYNTAX  Counter32
	UNITS "s"
	MAX-ACCESS  read-only
	STATUS current
	DESCRIPTION "Encoding errors"
	::= { e1StatisticsTableEntry 11 }

	e1rxRareErr   OBJECT-TYPE
	SYNTAX  Counter32
	UNITS "s"
	MAX-ACCESS  read-only
	STATUS current
	DESCRIPTION "Rare pulses error"
	::= { e1StatisticsTableEntry 12 }

	e1rxFastErr   OBJECT-TYPE
	SYNTAX  Counter32
	UNITS "s"
	MAX-ACCESS  read-only
	STATUS current
	DESCRIPTION "Fast pulses errors"
	::= { e1StatisticsTableEntry 13 }

	e1rxFDev   OBJECT-TYPE
	SYNTAX  Integer32
	UNITS "ppb"
	MAX-ACCESS  read-only
	STATUS current
	DESCRIPTION "The deviation of the frequency of the incoming flow from the internal"
	::= { e1StatisticsTableEntry 14 }

	e1rxCRC4   OBJECT-TYPE
	SYNTAX  Counter64
	UNITS "s"
	MAX-ACCESS  read-only
	STATUS current
	DESCRIPTION "Number of errors CRC4 on the receiver"
	::= { e1StatisticsTableEntry 15 }

	e1rxCRC4Sec   OBJECT-TYPE
	SYNTAX  Counter32
	UNITS "s"
	MAX-ACCESS  read-only
	STATUS current
	DESCRIPTION "Number of seconds during which CRC4 errors were detected on the receiver"
	::= { e1StatisticsTableEntry 16 }

	e1rxCRC4Rem   OBJECT-TYPE
	SYNTAX  Counter32
	UNITS "s"
	MAX-ACCESS  read-only
	STATUS current
	DESCRIPTION "The number of seconds in which errors in the CRC-4 error indication bits were detected at the receiver"
	::= { e1StatisticsTableEntry 17 }

	e1rxMfAS   OBJECT-TYPE
	SYNTAX  Counter32
	UNITS "s"
	MAX-ACCESS  read-only
	STATUS current
	DESCRIPTION "Number of seconds during which multiframe synchronization errors on the receiver were detected"
	::= { e1StatisticsTableEntry 18 }

	e1txOkCnt   OBJECT-TYPE
	SYNTAX  Counter32
	UNITS	"s"
	MAX-ACCESS  read-only
	STATUS current
	DESCRIPTION "No errors detected"
	::= { e1StatisticsTableEntry 102 }


	e1txNOS   OBJECT-TYPE
	SYNTAX  Counter32
	UNITS	"s"
	MAX-ACCESS  read-only
	STATUS current
	DESCRIPTION "No signal detected"
	::= { e1StatisticsTableEntry 103 }

	e1txAIS   OBJECT-TYPE
	SYNTAX  Counter32
	UNITS	"s"
	MAX-ACCESS  read-only
	STATUS current
	DESCRIPTION "Alarm Indication Signal"
	::= { e1StatisticsTableEntry 104 }

	e1txAZS   OBJECT-TYPE
	SYNTAX  Counter32
	UNITS	"s"
	MAX-ACCESS  read-only
	STATUS current
	DESCRIPTION "All Zeros Signal"
	::= { e1StatisticsTableEntry 105 }

	e1txLOS   OBJECT-TYPE
	SYNTAX  Counter32
	UNITS	"s"
	MAX-ACCESS  read-only
	STATUS current
	DESCRIPTION "Loss of frame"
	::= { e1StatisticsTableEntry 106 }

	e1txRAI   OBJECT-TYPE
	SYNTAX  Counter32
	UNITS	"s"
	MAX-ACCESS  read-only
	STATUS current
	DESCRIPTION "Remote Alarm indication"
	::= { e1StatisticsTableEntry 107 }

	e1txPRBS   OBJECT-TYPE
	SYNTAX  Counter32
	UNITS	"s"
	MAX-ACCESS  read-only
	STATUS current
	DESCRIPTION "PRBS Error. Valid only in PRBS Test/check mode"
	::= { e1StatisticsTableEntry 108 }

	e1txLock   OBJECT-TYPE
	SYNTAX  Counter32
	UNITS	"s"
	MAX-ACCESS  read-only
	STATUS current
	DESCRIPTION "TX+/TX- lock detected"
	::= { e1StatisticsTableEntry 112 }


	e1Start   OBJECT-TYPE
	SYNTAX  DateAndTime
	MAX-ACCESS  read-only
	STATUS current
	DESCRIPTION "Time of statistic capture start"
	::= { e1StatisticsTableEntry 113 }

	e1Finish   OBJECT-TYPE
	SYNTAX  DateAndTime
	MAX-ACCESS  read-only
	STATUS current
	DESCRIPTION "Time of statistic capture finish"
	::= { e1StatisticsTableEntry 114 }

	e1Total   OBJECT-TYPE
	SYNTAX  Counter32
	UNITS	"s"
	MAX-ACCESS  read-only
	STATUS current
	DESCRIPTION "Total second captured"
	::= { e1StatisticsTableEntry 115 }

	e1txFDev   OBJECT-TYPE
	SYNTAX  Integer32
	UNITS	"ppb"
	MAX-ACCESS  read-only
	STATUS current
	DESCRIPTION "The deviation of the frequency of the outgoing stream from the internal one, in ppb"
	::= { e1StatisticsTableEntry 116 }

	e1txCRC4Sec   OBJECT-TYPE
	SYNTAX  Counter32
	UNITS	"s"
	MAX-ACCESS  read-only
	STATUS current
	DESCRIPTION "Number of seconds during which CRC4 errors were detected on the transmitter"
	::= { e1StatisticsTableEntry 117 }

	e1txCRC4Rem   OBJECT-TYPE
	SYNTAX  Counter32
	UNITS	"s"
	MAX-ACCESS  read-only
	STATUS current
	DESCRIPTION "The number of seconds in which errors were detected in the CRC-4 error indication bits on the transmitter"
	::= { e1StatisticsTableEntry 118 }

	e1txMfAS   OBJECT-TYPE
	SYNTAX  Counter32
	UNITS	"s"
	MAX-ACCESS  read-only
	STATUS current
	DESCRIPTION "The number of seconds during which multiframe synchronization errors on the transmitter were detected"
	::= { e1StatisticsTableEntry 119 }

	e1GroupStat OBJECT-GROUP
	OBJECTS {
			e1rxOkCnt,
			e1rxNOS,
			e1rxAIS,
			e1rxAZS,
			e1rxLOS,
			e1rxRAI,
			e1rxPRBS,
			e1rxTest,
			e1rxCodeErr,
			e1rxRareErr,
			e1rxFastErr,
			e1rxFDev,
			e1rxCRC4,
			e1rxCRC4Sec,
			e1rxCRC4Rem,
			e1rxMfAS,
			e1txOkCnt,
			e1txNOS,
			e1txAIS,
			e1txAZS,
			e1txLOS,
			e1txRAI,
			e1txPRBS,
			e1txLock,
			e1Start,
			e1Finish,
			e1Total,
			e1txFDev,
			e1txCRC4Sec,
			e1txCRC4Rem,
			e1txMfAS
		}
	STATUS current
	DESCRIPTION
		"A collection of objects providing statistic information about e1 interfaces"
--	::= { e1 15 }
	::= { muxGroups 4 }

	tdmStatisticsTable					OBJECT-TYPE
	SYNTAX					SEQUENCE OF TDMStatisticsEntry
	MAX-ACCESS					not-accessible
	STATUS					current
	DESCRIPTION				"A list of TDM channels"
	::= { e1 9 }


  	TDMStatisticsEntry ::=
    SEQUENCE {
			tdmStChIndex 	Integer32,
			tdmResend	Counter32,
			tdmLost		Counter32,
			tdmOvf		Counter32,
			tdmUndf		Counter32,
			tdmIgnored	Counter32,
			tdmInterp	Counter32,
			tdmResync	Counter32,
			tdmValid	Counter32,
			tdmSlipAdd	Counter32,
			tdmSlipRem	Counter32,
			tdmLostReq	Counter32,
			tdmRestored	Counter32,
			tdmStart	DateAndTime,
			tdmFinish	DateAndTime,
			tdmAvgSpeed	Integer32,
			tdmAvgJB	Integer32,
			tdmMinJB	Integer32,
			tdmMaxJB	Integer32,
			tdmRecommenedJB	Integer32,
			tdmFatal	Counter32,
			tdmTxDiscards	Counter32,
			tdmBandwidth	Integer32
           }

	tdmStatisticsTableEntry			OBJECT-TYPE
	SYNTAX					TDMStatisticsEntry
	MAX-ACCESS					not-accessible
	STATUS					current
	DESCRIPTION				"A list of TDM statistics"
	INDEX   { tdmStChIndex }
	::= { tdmStatisticsTable 1}


	tdmStChIndex   OBJECT-TYPE
	SYNTAX  Integer32(0..128)
	MAX-ACCESS  not-accessible
	STATUS current
	DESCRIPTION "Channel number"
	::= { tdmStatisticsTableEntry 1 }

	tdmResend   OBJECT-TYPE
	SYNTAX  Counter32
	UNITS	"frames"
	MAX-ACCESS  read-only
	STATUS current
	DESCRIPTION "Total frames resend to remote side"
	::= { tdmStatisticsTableEntry 2 }


	tdmLost   OBJECT-TYPE
	SYNTAX  Counter32
	UNITS	"frames"
	MAX-ACCESS  read-only
	STATUS current
	DESCRIPTION "Lost of frame events count"
	::= { tdmStatisticsTableEntry 3 }

	tdmOvf   OBJECT-TYPE
	SYNTAX  Counter32
	UNITS	"times"
	MAX-ACCESS  read-only
	STATUS current
	DESCRIPTION "Overflow of jitter buffer events"
	::= { tdmStatisticsTableEntry 4 }

	tdmUndf   OBJECT-TYPE
	SYNTAX  Counter32
	UNITS	"Times"
	MAX-ACCESS  read-only
	STATUS current
	DESCRIPTION "Underflow of jitter buffer events"
	::= { tdmStatisticsTableEntry 5 }

	tdmIgnored   OBJECT-TYPE
	SYNTAX  Counter32
	UNITS	"frames"
	MAX-ACCESS  read-only
	STATUS current
	DESCRIPTION "Frames ignored on recv (duplicate or too old)"
	::= { tdmStatisticsTableEntry 6 }

	tdmInterp   OBJECT-TYPE
	SYNTAX  Counter32
	UNITS "125us"
	MAX-ACCESS  read-only
	STATUS current
	DESCRIPTION "E1 Frame resend to E1 side, because of no data on TDMoP Recv"
	::= { tdmStatisticsTableEntry 7 }

	tdmResync   OBJECT-TYPE
	SYNTAX  Counter32
	UNITS	"times"
	MAX-ACCESS  read-only
	STATUS current
	DESCRIPTION "Restart TDMoP sync"
	::= { tdmStatisticsTableEntry 8 }

	tdmValid   OBJECT-TYPE
	SYNTAX  Counter32
	UNITS	"frames"
	MAX-ACCESS  read-only
	STATUS current
	DESCRIPTION "Total valid TDMoP frames recvd"
	::= { tdmStatisticsTableEntry 9 }

	tdmSlipAdd   OBJECT-TYPE
	SYNTAX  Counter32
	UNITS	"times"
	MAX-ACCESS  read-only
	STATUS current
	DESCRIPTION "Slip add events"
	::= { tdmStatisticsTableEntry 10 }

	tdmSlipRem   OBJECT-TYPE
	SYNTAX  Counter32
	UNITS	"times"
	MAX-ACCESS  read-only
	STATUS current
	DESCRIPTION "Slip remove events"
	::= { tdmStatisticsTableEntry 11 }

	tdmLostReq   OBJECT-TYPE
	SYNTAX  Counter32
	UNITS	"frames"
	MAX-ACCESS  read-only
	STATUS current
	DESCRIPTION "Lost requests send to remote side"
	::= { tdmStatisticsTableEntry 12 }

	tdmRestored   OBJECT-TYPE
	SYNTAX  Counter32
	UNITS	"frames"
	MAX-ACCESS  read-only
	STATUS current
	DESCRIPTION "Lost frames, that recvd in valid time (after lost request or reordered)"
	::= { tdmStatisticsTableEntry 13 }

	tdmStart   OBJECT-TYPE
	SYNTAX  DateAndTime
	MAX-ACCESS  read-only
	STATUS current
	DESCRIPTION "Time of statistics start"
	::= { tdmStatisticsTableEntry 14 }


	tdmFinish   OBJECT-TYPE
	SYNTAX  DateAndTime
	MAX-ACCESS  read-only
	STATUS current
	DESCRIPTION "Time of statistics finish"
	::= { tdmStatisticsTableEntry 15 }

	tdmAvgSpeed   OBJECT-TYPE
	SYNTAX  Integer32
	UNITS	"ppb"
	MAX-ACCESS  read-only
	STATUS current
	DESCRIPTION "Avg E1 tx freq deviation"
	::= { tdmStatisticsTableEntry 16 }

	tdmAvgJB   OBJECT-TYPE
	SYNTAX  Integer32
	UNITS	"us"
	MAX-ACCESS  read-only
	STATUS current
	DESCRIPTION "Avg Jitter buffer size"
	::= { tdmStatisticsTableEntry 17 }

	tdmMinJB   OBJECT-TYPE
	SYNTAX  Integer32
	UNITS	"ms"
	MAX-ACCESS  read-only
	STATUS current
	DESCRIPTION "Min jitter buffer for 1 sec"
	::= { tdmStatisticsTableEntry 18 }

	tdmMaxJB   OBJECT-TYPE
	SYNTAX  Integer32
	UNITS	"ms"
	MAX-ACCESS  read-only
	STATUS current
	DESCRIPTION "Maximum jitter buffer for 1 sec"
	::= { tdmStatisticsTableEntry 19 }

	tdmRecommenedJB   OBJECT-TYPE
	SYNTAX  Integer32
	UNITS	"ms"
	MAX-ACCESS  read-only
	STATUS current
	DESCRIPTION "Recomended jitter buffer, using current network statistics and configuration of channel"
	::= { tdmStatisticsTableEntry 20 }

	tdmFatal   OBJECT-TYPE
	SYNTAX  Counter32
	UNITS	"frames"
	MAX-ACCESS  read-only
	STATUS current
	DESCRIPTION "The number of hardware errors"
	::= { tdmStatisticsTableEntry 21 }

	tdmTxDiscards   OBJECT-TYPE
	SYNTAX  Counter32
	UNITS	"frames"
	MAX-ACCESS  read-only
	STATUS current
	DESCRIPTION "The number of packets that were discarded and not processed due to the overflow of the output queue"
	::= { tdmStatisticsTableEntry 22 }

	tdmBandwidth   OBJECT-TYPE
	SYNTAX  Integer32
	UNITS	"kbps"
	MAX-ACCESS  read-only
	STATUS current
	DESCRIPTION "Current bandwidth"
	::= { tdmStatisticsTableEntry 23 }

	tdmGroupStat OBJECT-GROUP
	OBJECTS {
			tdmResend,
			tdmLost,
			tdmOvf,
			tdmUndf,
			tdmIgnored,
			tdmInterp,
			tdmResync,
			tdmValid,
			tdmSlipAdd,
			tdmSlipRem,
			tdmLostReq,
			tdmRestored,
			tdmStart,
			tdmFinish,
			tdmAvgSpeed,
			tdmAvgJB,
			tdmMinJB,
			tdmMaxJB,
			tdmRecommenedJB,
			tdmFatal,
			tdmTxDiscards,
			tdmBandwidth
		}
	STATUS current
	DESCRIPTION
		"A collection of objects providing statistic information about TDMoP interfaces"
--	::= { e1 16 }
	::= { muxGroups 5 }

	e1traps 			OBJECT IDENTIFIER ::=	{ e1 10 }
	e1trapsPrefix 	OBJECT IDENTIFIER ::=	{ e1traps 0 }

	e1LinkChange NOTIFICATION-TYPE
--    OBJECTS { e1ChIndex, e1RecvStatus, e1SendStatus}
    OBJECTS { e1RecvStatus, e1SendStatus}
    STATUS  current
    DESCRIPTION
            "A e1linkChange signifies that the SNMP entity, acting in
            an agent role, has detected that the send or recv status changed"
    ::= { e1trapsPrefix 1 }

	tdmLinkDown NOTIFICATION-TYPE
--    OBJECTS { tdmChIndex, tdmAdminStatus, tdmLinkStatus }
    OBJECTS { tdmAdminStatus, tdmLinkStatus }
    STATUS  current
    DESCRIPTION
            "A tdmlinkDown signifies that the SNMP entity, acting in
            an agent role, has detected a link down"
    ::= { e1trapsPrefix 2 }

	tdmLinkUp NOTIFICATION-TYPE
--    OBJECTS { tdmChIndex, tdmAdminStatus, tdmLinkStatus }
    OBJECTS { tdmAdminStatus, tdmLinkStatus }
    STATUS  current
    DESCRIPTION
            " tdmlinkDown signifies that the SNMP entity, acting in
            an agent role, has detected a link up"
    ::= { e1trapsPrefix 3 }

	tdmRedundancyTable			OBJECT-TYPE
	SYNTAX					SEQUENCE OF TDMChRedundancyEntrySeq
	MAX-ACCESS				not-accessible
	STATUS					current
	DESCRIPTION				"A list of E1 channels for reservation settings"
	::= { e1 11 }

	TDMChRedundancyEntrySeq ::=
	SEQUENCE {
			tdmRedundancyIndex Integer32,
			tdmRedundancyEnabled INTEGER,
			tdmRedundancyRemoteIP IpAddress,
			tdmRedundancyVLANID Integer32,
			tdmRedundancyDSCP DisplayString,
			tdmRedundancyUseIP INTEGER,
			tdmRedundancyVLANPri Integer32
	}

	tdmRedundancyTableEntry			OBJECT-TYPE
	SYNTAX					TDMChRedundancyEntrySeq
	MAX-ACCESS				not-accessible
	STATUS					current
	DESCRIPTION				"Reservation settings for E1 streams"
	INDEX   { tdmRedundancyIndex }
	::= { tdmRedundancyTable 1}

	tdmRedundancyIndex   OBJECT-TYPE
	SYNTAX  Integer32(0..128)
	MAX-ACCESS not-accessible
	STATUS current
	DESCRIPTION "Index of TDM redundancy connection"
	::= { tdmRedundancyTableEntry 1 }

	tdmRedundancyEnabled   OBJECT-TYPE
	SYNTAX  INTEGER { enabled(1),disabled(2)}
	MAX-ACCESS  read-write
	STATUS current
	DESCRIPTION "Redundance on the channel is enabled"
	::= { tdmRedundancyTableEntry 2 }

	tdmRedundancyRemoteIP   OBJECT-TYPE
	SYNTAX  IpAddress
	MAX-ACCESS  read-write
	STATUS current
	DESCRIPTION "IP address of the oncoming device."
	::= { tdmRedundancyTableEntry 3 }

	tdmRedundancyVLANID   OBJECT-TYPE
	SYNTAX  Integer32
	MAX-ACCESS  read-write
	STATUS current
	DESCRIPTION "Transmitter VLAN ID"
	::= { tdmRedundancyTableEntry 4 }

	tdmRedundancyDSCP   OBJECT-TYPE
	SYNTAX  DisplayString
	MAX-ACCESS  read-write
	STATUS current
	DESCRIPTION "IP DSCP (0-63,af[1..4][1..3],cs[1..7],default,ef)"
	::= { tdmRedundancyTableEntry 5 }

	tdmRedundancyUseIP   OBJECT-TYPE
	SYNTAX  INTEGER { use(1), dontuse(2) }
	MAX-ACCESS  read-write
	STATUS current
	DESCRIPTION "Use - send over UDP/IP, dontuse - over proprietary protocol id over ethernet"
	::= { tdmRedundancyTableEntry 6 }

	tdmRedundancyVLANPri   OBJECT-TYPE
	SYNTAX  Integer32
	MAX-ACCESS  read-write
	STATUS current
	DESCRIPTION "Transmitter VLAN Priority"
	::= { tdmRedundancyTableEntry 7 }

	tdmRedundancyGroup OBJECT-GROUP
	OBJECTS {
	tdmRedundancyEnabled,
	tdmRedundancyRemoteIP,
	tdmRedundancyVLANID,
	tdmRedundancyDSCP,
	tdmRedundancyUseIP,
	tdmRedundancyVLANPri
	}
	STATUS current
	DESCRIPTION
	"A collection of objects providing minimal information about tdm redundancy mappings"
	::= { muxGroups 13 }


	eth	OBJECT IDENTIFIER ::=	{emux 19 }

	vlanTable					OBJECT-TYPE
	SYNTAX					SEQUENCE OF VLANTableEntrySeq
	MAX-ACCESS					not-accessible
	STATUS					current
	DESCRIPTION				"A list of VLANS"
	::= { eth 3 }


  	VLANTableEntrySeq ::=
    SEQUENCE {
			vlanID 	Integer32


           }

	vlanTableEntry			OBJECT-TYPE
	SYNTAX					VLANTableEntrySeq
	MAX-ACCESS					not-accessible
	STATUS					current
	DESCRIPTION				"A list of VLANS"
	INDEX   { vlanID }
	::= { vlanTable 1}

	vlanID   OBJECT-TYPE
	SYNTAX  Integer32(0..4095)
	MAX-ACCESS  read-only
	STATUS current
	DESCRIPTION "VLAN identifier"
	::= { vlanTableEntry 1 }

	vlanGroup OBJECT-GROUP
	OBJECTS {
			vlanID
		}
	STATUS current
	DESCRIPTION
		"A collection of objects providing VLAN information about VLAN interfaces"
--	::= { eth 4 }
	::= { muxGroups 6 }

	muxip	OBJECT IDENTIFIER ::=	{general 2 }
	ipcurrent OBJECT IDENTIFIER ::=	{muxip 1 }

	cNetIP OBJECT-TYPE
	SYNTAX IpAddress
	MAX-ACCESS	read-write
	STATUS current
	DESCRIPTION "Device current ip"
	::= {ipcurrent 1}

	cNetMask OBJECT-TYPE
	SYNTAX IpAddress
	MAX-ACCESS	read-write
	STATUS current
	DESCRIPTION "Device current ip mask"
	::= {ipcurrent 2}

	cNetGateway OBJECT-TYPE
	SYNTAX IpAddress
	MAX-ACCESS	read-write
	STATUS current
	DESCRIPTION "Device current gateway"
	::= {ipcurrent 3}

	cDefaultVlan OBJECT-TYPE
	SYNTAX Integer32
	MAX-ACCESS	read-write
	STATUS current
	DESCRIPTION "managment vlan"
	::= {ipcurrent 4}

	cDefaultVlanPri OBJECT-TYPE
	SYNTAX Integer32
	MAX-ACCESS	read-write
	STATUS current
	DESCRIPTION "managment vlan priority"
	::= {ipcurrent 5}

	cNetTrustAll OBJECT-TYPE
	SYNTAX INTEGER { yes(1),no(2) }
	MAX-ACCESS	read-write
	STATUS current
	DESCRIPTION "Trust any source ip"
	::= {ipcurrent 6}

	cNetTrustLocal OBJECT-TYPE
	SYNTAX INTEGER { yes(1),no(2) }
	MAX-ACCESS	read-write
	STATUS current
	DESCRIPTION "Trust local source ip"
	::= {ipcurrent 7}

	cNetTrustUnkVlan OBJECT-TYPE
	SYNTAX INTEGER { yes(1),no(2) }
	MAX-ACCESS	read-write
	STATUS current
	DESCRIPTION "Trust unknown vlan"
	::= {ipcurrent 8}

	cDNS1 OBJECT-TYPE
	SYNTAX IpAddress
	MAX-ACCESS	read-write
	STATUS current
	DESCRIPTION "Current DNS server"
	::= {ipcurrent 9}

	cPhysicalAddr OBJECT-TYPE
	SYNTAX      MacAddress
	MAX-ACCESS  read-only
	STATUS      current
	DESCRIPTION "Current main MAC address"
	::= {ipcurrent 10}

	cSecondaryMAC OBJECT-TYPE
	SYNTAX      MacAddress
	MAX-ACCESS  read-only
	STATUS      current
	DESCRIPTION "Current secondary MAC address"
	::= {ipcurrent 11}

	ipcurrentGroup OBJECT-GROUP
	OBJECTS {
			cNetIP,
			cNetMask,
			cNetGateway,
			cDefaultVlan,
			cDefaultVlanPri,
			cNetTrustAll,
			cNetTrustLocal,
			cNetTrustUnkVlan,
			cDNS1,
			cPhysicalAddr,
			cSecondaryMAC
		}
	STATUS current
	DESCRIPTION
		"A collection of objects about current network settings"
--	::= { muxip 4 }
	::= { muxGroups 7 }

	ipstored OBJECT IDENTIFIER ::=	{muxip 2 }

	sNetIP OBJECT-TYPE
	SYNTAX IpAddress
	MAX-ACCESS	read-write
	STATUS current
	DESCRIPTION "Device current ip"
	::= {ipstored 1}

	sNetMask OBJECT-TYPE
	SYNTAX IpAddress
	MAX-ACCESS	read-write
	STATUS current
	DESCRIPTION "Device current ip mask"
	::= {ipstored 2}

	sNetGateway OBJECT-TYPE
	SYNTAX IpAddress
	MAX-ACCESS	read-write
	STATUS current
	DESCRIPTION "Device current gateway"
	::= {ipstored 3}

	sDefaultVlan OBJECT-TYPE
	SYNTAX Integer32
	MAX-ACCESS	read-write
	STATUS current
	DESCRIPTION "managment vlan"
	::= {ipstored 4}

	sDefaultVlanPri OBJECT-TYPE
	SYNTAX Integer32
	MAX-ACCESS	read-write
	STATUS current
	DESCRIPTION "managment vlan priority"
	::= {ipstored 5}

	sNetTrustAll OBJECT-TYPE
	SYNTAX INTEGER { yes(1),no(2) }
	MAX-ACCESS	read-write
	STATUS current
	DESCRIPTION "Trust any source ip"
	::= {ipstored 6}

	sNetTrustLocal OBJECT-TYPE
	SYNTAX INTEGER { yes(1),no(2) }
	MAX-ACCESS	read-write
	STATUS current
	DESCRIPTION "Trust local source ip"
	::= {ipstored 7}

	sNetTrustUnkVlan OBJECT-TYPE
	SYNTAX INTEGER { yes(1),no(2) }
	MAX-ACCESS	read-write
	STATUS current
	DESCRIPTION "Trust unknown vlan"
	::= {ipstored 8}

	sDNS1 OBJECT-TYPE
	SYNTAX IpAddress
	MAX-ACCESS	read-write
	STATUS current
	DESCRIPTION "Stored DNS server"
	::= {ipstored 9}

	sPhysicalAddr OBJECT-TYPE
	SYNTAX      MacAddress
	MAX-ACCESS  read-only
	STATUS      current
	DESCRIPTION "Stored main MAC address"
	::= {ipstored 10}

	sSecondaryMAC OBJECT-TYPE
	SYNTAX      MacAddress
	MAX-ACCESS  read-only
	STATUS      current
	DESCRIPTION "Stored secondary MAC address"
	::= {ipstored 11}

	ipstoredGroup OBJECT-GROUP
	OBJECTS {
			sNetIP,
			sNetMask,
			sNetGateway,
			sDefaultVlan,
			sDefaultVlanPri,
			sNetTrustAll,
			sNetTrustLocal,
			sNetTrustUnkVlan,
			sDNS1,
			sPhysicalAddr,
			sSecondaryMAC
		}
	STATUS current
	DESCRIPTION
		"A collection of objects about stored network settings"
--	::= { muxip 5 }
	::= { muxGroups 8 }

	hostsTable				OBJECT-TYPE
	SYNTAX					SEQUENCE OF HostsTableEntrySeq
	MAX-ACCESS					not-accessible
	STATUS					current
	DESCRIPTION				"A list of trusted hosts"
	::= { muxip 3 }


  	HostsTableEntrySeq ::=
    SEQUENCE {
			hostIndex		Integer32,
			hostNetwork 	IpAddress,
			hostMask		IpAddress
           }

	hostsTableEntry			OBJECT-TYPE
	SYNTAX					HostsTableEntrySeq
	MAX-ACCESS					not-accessible
	STATUS					current
	DESCRIPTION				"A list of trusted hosts"
	INDEX		{hostIndex}
	::= { hostsTable 1}

	hostIndex   OBJECT-TYPE
	SYNTAX  Integer32(0..31)
	MAX-ACCESS  not-accessible
	STATUS current
	DESCRIPTION "Trusted network id"
	::= { hostsTableEntry 1 }

	hostNetwork   OBJECT-TYPE
	SYNTAX  IpAddress
	MAX-ACCESS  read-write
	STATUS current
	DESCRIPTION "Trusted network id"
	::= { hostsTableEntry 2 }

	hostMask  OBJECT-TYPE
	SYNTAX  IpAddress
	MAX-ACCESS  read-write
	STATUS current
	DESCRIPTION "Trusted network mask"
	::= { hostsTableEntry 3 }

	hostsGroup OBJECT-GROUP
	OBJECTS {
			hostNetwork,
			hostMask
		}
	STATUS current
	DESCRIPTION
		"A collection of objects about trusted hosts"
--	::= { muxip 6 }
	::= { muxGroups 9 }

	adc	OBJECT IDENTIFIER ::=	{emux 21 }
	adcTable				OBJECT-TYPE
	SYNTAX					SEQUENCE OF AdcTableEntrySeq
	MAX-ACCESS				not-accessible
	STATUS					current
	DESCRIPTION				"A list of ADC parameters"
	::= { adc 1 }


  	AdcTableEntrySeq ::=
    SEQUENCE {
			adcIndex	Integer32,
			adcName 	DisplayString,
			adcValue	Float,
			adcType 	DisplayString,
			adcState 	INTEGER
           }

	adcTableEntry			OBJECT-TYPE
	SYNTAX				AdcTableEntrySeq
	MAX-ACCESS			not-accessible
	STATUS				current
	DESCRIPTION			"A list of ADC parameters"
	INDEX		{adcIndex}
	::= { adcTable 1}

	adcIndex   OBJECT-TYPE
	SYNTAX  Integer32(0..31)
	MAX-ACCESS  not-accessible
	STATUS current
	DESCRIPTION "ADC id"
	::= { adcTableEntry 1 }

	adcName OBJECT-TYPE
	SYNTAX DisplayString
	MAX-ACCESS  read-only
	STATUS current
	DESCRIPTION "ADC Name"
	::= { adcTableEntry 2 }

	adcValue OBJECT-TYPE
	SYNTAX Float
	MAX-ACCESS  read-only
	STATUS current
	DESCRIPTION "ADC Value"
	::= { adcTableEntry 3 }

	adcType OBJECT-TYPE
	SYNTAX DisplayString
	MAX-ACCESS  read-only
	STATUS current
	DESCRIPTION "unit of measurement"
	::= { adcTableEntry 4 }

	adcState OBJECT-TYPE
	SYNTAX  INTEGER { normal(0), errHigh(1), errLow(2), warnHigh(3), warnLow(4), down(5) }
	MAX-ACCESS read-only
	STATUS current
	DESCRIPTION "ADC State"
	::= { adcTableEntry 5 }


	adcGroup OBJECT-GROUP
	OBJECTS {
			adcName,
			adcValue,
			adcType,
			adcState
		}
	STATUS current
	DESCRIPTION
		"A collection of objects about ADC"
--	::= { adc 2 }
	::= { muxGroups 10 }

	e1trapsGroup NOTIFICATION-GROUP
	NOTIFICATIONS {
			e1LinkChange,
			tdmLinkDown,
			tdmLinkUp
			}
	STATUS current
	DESCRIPTION
		"A collection of notifications providing traps"
	::= { muxGroups 11 }

	dyingGaspNotifications	OBJECT IDENTIFIER ::=	{ emux 22 }
	dyingGaspTraps 	OBJECT IDENTIFIER ::=	{ dyingGaspNotifications 0 }

	dyingGaspTrap NOTIFICATION-TYPE
--	OBJECTS { sysID }
	STATUS  current
	DESCRIPTION
		"I am dying"
	::= { dyingGaspTraps 1 }

	dyingGaspTrapsGroup NOTIFICATION-GROUP
	NOTIFICATIONS {
		dyingGaspTrap
	}
	STATUS current
	DESCRIPTION
		"A collection of notifications dying gasp (traps)"
	::= { muxGroups 12 }


emuxCompliance MODULE-COMPLIANCE
    STATUS      current
    DESCRIPTION
        "The compliance statement for device"
    MODULE
        MANDATORY-GROUPS {
            muxBaseGroup,
			e1Group,
			tdmGroup,
			e1GroupStat,
			tdmGroupStat,
			e1trapsGroup,
			vlanGroup,
			ipcurrentGroup,
			ipstoredGroup,
			hostsGroup,
			adcGroup,
			tdmRedundancyGroup
        }

       GROUP dyingGaspTrapsGroup
       DESCRIPTION
           "Group of objects describing notifications (traps)"
    ::= { muxCompliances 1 }

END
