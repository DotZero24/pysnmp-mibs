ELTEX-IP-UNNUMBERED-MIB DEFINITIONS ::= BEGIN

-- Title:   ELTEX IP UNNUMBERED MIB
-- Version: 1.0
-- Date:    16-Oct-2017

IMPORTS
    MODULE-IDENTITY,
    OBJECT-TYPE
        FROM SNMPv2-SMI

    ifIndex
        FROM IF-MIB

    RowStatus
        FROM SNMPv2-TC

    eltexLtd
        FROM ELTEX-SMI-ACTUAL

    InterfaceIndex
        FROM IF-MIB;

eltexIpUnnumberedMIB MODULE-IDENTITY
    LAST-UPDATED "201710160000Z"
    ORGANIZATION "Eltex Enterprise Co, Ltd."
    CONTACT-INFO
        "eltex-co.ru"
    DESCRIPTION
        "The ELTEX-IP-UNNUMBERED is used to describe the relation
        between interface and unnumbered interface."
    REVISION "201710160000Z"
    DESCRIPTION
        "Initial version of this MIB."
    ::= { eltexLtd 42 }

eltexIpUnnumberedMIBObjects   OBJECT IDENTIFIER ::= { eltexIpUnnumberedMIB 1 }

eltexIpUnnumberedInterfaceTable OBJECT-TYPE
    SYNTAX      SEQUENCE OF EltexIpUnnumberedInterfaceEntry
    MAX-ACCESS  not-accessible
    STATUS      current
    DESCRIPTION
        "A table contains ip unnumbered interfaces."
    ::= { eltexIpUnnumberedMIBObjects 1 }

eltexIpUnnumberedInterfaceEntry OBJECT-TYPE
    SYNTAX      EltexIpUnnumberedInterfaceEntry
    MAX-ACCESS  not-accessible
    STATUS      current
    DESCRIPTION
        "The row definition for this table."
    INDEX   {ifIndex}
    ::= { eltexIpUnnumberedInterfaceTable 1 }

EltexIpUnnumberedInterfaceEntry ::= SEQUENCE {
    eltexIpUnnumberedParentIfIndex
        InterfaceIndex,
    eltexIpUnnumberedRowStatus
        RowStatus
}

eltexIpUnnumberedParentIfIndex OBJECT-TYPE
    SYNTAX      InterfaceIndex
    MAX-ACCESS  read-create
    STATUS      current
    DESCRIPTION
        "A unique value, greater than zero, for each
         interface that borrows ip address to
         another interface."
    ::= { eltexIpUnnumberedInterfaceEntry 1 }

eltexIpUnnumberedRowStatus OBJECT-TYPE
    SYNTAX       RowStatus
    MAX-ACCESS   read-create
    STATUS       current
    DESCRIPTION
        "This variable displays the status of  the  entry."
    ::= { eltexIpUnnumberedInterfaceEntry 2 }

END
