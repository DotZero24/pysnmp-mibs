ELTEX-MES-IP-OSPF-IF-MIB DEFINITIONS ::= BEGIN

-- Title:      Eltex's MES Switches Private MIB
-- Version:    1.00
-- Date:       24-Feb-2014

IMPORTS
    eltMes                       FROM ELTEX-MES
    eltMesOspf                   FROM ELTEX-MES-IP
    IpAddress,
    OBJECT-TYPE                  FROM SNMPv2-SMI
    TruthValue,
    RowStatus                    FROM SNMPv2-TC
    PortList                     FROM Q-BRIDGE-MIB;


eltIpOspfIfTable OBJECT-TYPE
        SYNTAX   SEQUENCE OF EltIpOspfIfEntry
        MAX-ACCESS   not-accessible
        STATUS   current
        DESCRIPTION
           "The OSPF Interface Table describes the  inter-
           faces from the viewpoint of OSPF."
       REFERENCE
          "OSPF Version 2, Appendix C.3  Router  interface
          parameters"
    ::= { eltMesOspf 2 }

eltIpOspfIfEntry OBJECT-TYPE
        SYNTAX EltIpOspfIfEntry
        MAX-ACCESS   not-accessible
        STATUS   current
        DESCRIPTION
           "The OSPF Interface Entry describes one  inter-
           face from the viewpoint of OSPF."
       INDEX { eltOspfIfAddress }
       ::= { eltIpOspfIfTable 1 }

EltIpOspfIfEntry ::=
    SEQUENCE {
        eltOspfIfAddress         IpAddress,
        eltOspfIfPassiveDefault  TruthValue,
        eltOspfIfPassiveList     PortList,
        eltOspfIfStatus          RowStatus
    }

eltOspfIfAddress OBJECT-TYPE
        SYNTAX   IpAddress
        MAX-ACCESS   read-write
        STATUS   current
        DESCRIPTION
           "The IP address of this OSPF interface."
       ::= { eltIpOspfIfEntry 1 }

eltOspfIfPassiveDefault OBJECT-TYPE
        SYNTAX        TruthValue
        MAX-ACCESS    read-write
        STATUS        current
        DESCRIPTION
            " "
        DEFVAL { false }
        ::= { eltIpOspfIfEntry 2 }

eltOspfIfPassiveList OBJECT-TYPE
        SYNTAX        PortList
        MAX-ACCESS    read-write
        STATUS        current
        DESCRIPTION
            "Indicates whether the OSPF interface on this Vlan is
            Passive or not. Passive interfaces do not send routing
            updates. A true value indicates that the interface is passive."
        ::= { eltIpOspfIfEntry 3 }

eltOspfIfStatus OBJECT-TYPE
        SYNTAX   RowStatus
        MAX-ACCESS   read-create
        STATUS   current
        DESCRIPTION
           "This variable displays the status of  the  en-
           try."
       ::= { eltIpOspfIfEntry 4 }

END
