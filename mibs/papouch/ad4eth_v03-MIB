--*********************************
-- MIB table for AD4ETH
-- AD4ETH is Ethernet A/D converter
--
-- by Miroslav Steiger
-- Copyringht (c) 2007 by www.papouch.com

--*********************************

ad4eth_v03-MIB DEFINITIONS ::= BEGIN

IMPORTS
--	MODULE-IDENTITY,
--	OBJECT-TYPE,
--	NOTIFICATION-TYPE,
		enterprises,
		IpAddress,
		Counter,
		Gauge,
		TimeTicks
    	FROM RFC1155-SMI
    OBJECT-TYPE
		FROM RFC-1212
	DisplayString
		FROM RFC1213-MIB
	TRAP-TYPE
		FROM RFC-1215
    ;

papouchProjekt	   OBJECT IDENTIFIER ::= { enterprises 18248 }
ad4eth		       OBJECT IDENTIFIER ::= { papouchProjekt 17 }
version3            OBJECT IDENTIFIER ::= { ad4eth 3 }

device_var         OBJECT IDENTIFIER ::= { version3 1 }
table_channel      OBJECT IDENTIFIER ::= { version3 2 }
table_watchValue   OBJECT IDENTIFIER ::= { version3 3 }
--
-- Type Definitions
--

PositiveInteger ::= INTEGER (0..65535)
---
--- TABULKA PRO PARAMETRY pro cteni a zapis
---
 channelTable OBJECT-TYPE
	SYNTAX  SEQUENCE OF ChannelEntry
	ACCESS  not-accessible
	STATUS  current
	DESCRIPTION	""
 ::= { table_channel 1 }
 channelEntry OBJECT-TYPE
	SYNTAX  ChannelEntry
	ACCESS  not-accessible
	STATUS  current
	DESCRIPTION	""
	INDEX   { index }
 ::= { channelTable 1 }
 ChannelEntry ::=
    SEQUENCE {
        inCh_name
            DisplayString,
        inChStatus
            INTEGER,
        inChValue
            DisplayString,
        inChTroops
            DisplayString

    }

--
-- parametry pro cteni nastaveni jmena vstupu
--
--
-- OID 1.3.6.1.4.1.18248.17.3.2.1.1.1.1 - 4
--
inCh_name OBJECT-TYPE
    SYNTAX DisplayString
	ACCESS read-only
	STATUS current
	DESCRIPTION	"user name is user string"
::= { channelEntry 1 }
--
-- parametry pro cteni status mode
--
--
-- OID 1.3.6.1.4.1.18248.17.3.2.1.1.2.1 - 4
--
inChStatus  OBJECT-TYPE
	SYNTAX  	INTEGER
	ACCESS		read-only
	STATUS		current
	DESCRIPTION	"0 = OK,1 = Not available,2 = over-flow,3 = under-flow,4=ERR"
::= { channelEntry 2 }
--
-- OID 1.3.6.1.4.1.18248.17.3.2.1.1.3.1 - 4
--
inChValue  OBJECT-TYPE
	SYNTAX  	DisplayString
	ACCESS		read-only
	STATUS		current
	DESCRIPTION	""
::= { channelEntry 3 }
--
-- OID 1.3.6.1.4.1.18248.17.3.2.1.1.4.1 - 4
--
inChUnits  OBJECT-TYPE
	SYNTAX  	DisplayString
	ACCESS		read-only
	STATUS		current
	DESCRIPTION	""
::= { channelEntry 4 }

---
--- TABULKA PRO PARAMETRY HLIDANI
---
 watchValTable OBJECT-TYPE
	SYNTAX  SEQUENCE OF WatchValEntry
	ACCESS  not-accessible
	STATUS  current
	DESCRIPTION	""
 ::= { table_watchValue 1 }

 watchValEntry OBJECT-TYPE
	SYNTAX  WatchValEntry
	ACCESS  not-accessible
	STATUS  current
	DESCRIPTION	""
	INDEX   { index }
 ::= { watchValTable 1 }

WatchValEntry ::=
    SEQUENCE {
        modeWatch
            INTEGER,
        limitHi
            DisplayString,
        limitLo
            DisplayString,

        limitHy
            DisplayString
    }
--
-- OID 1.3.6.1.4.1.18248.17.3.3.1.1.1.1 - 4
--
modeWatch OBJECT-TYPE
	SYNTAX  	INTEGER(0..1)
	ACCESS		read-only
	STATUS		current
	DESCRIPTION	"1 = ON,0 = OFF"
::= { watchValEntry 1 }
--
-- OID 1.3.6.1.4.1.18248.17.3.3.1.1.2.1 - 4
--
limitHi OBJECT-TYPE
	SYNTAX  	DisplayString
	ACCESS		read-only
	STATUS		current
	DESCRIPTION	""
::= { watchValEntry 2 }
--
-- OID 1.3.6.1.4.1.18248.17.3.3.1.1.3.1 - 4
--
limitLo OBJECT-TYPE
	SYNTAX  	DisplayString
	ACCESS		read-only
	STATUS		current
	DESCRIPTION	""
::= { watchValEntry 3 }
--
-- OID 1.3.6.1.4.1.18248.17.3.3.1.1.4.1 - 4
--
limitHy OBJECT-TYPE
	SYNTAX  	DisplayString
	ACCESS		read-only
	STATUS		current
	DESCRIPTION	""
::= { watchValEntry 4 }
--
-- OID 1.3.6.1.4.1.18248.17.3.1.1.0
--
deviceName OBJECT-TYPE
	SYNTAX		DisplayString
	ACCESS		read-only
	STATUS		mandatory
	DESCRIPTION	"Device Name"
::= { device_var 1 }
--
-- OID 1.3.6.1.4.1.18248.17.3.1.2.0
--
psAlarmString OBJECT-TYPE
	SYNTAX		DisplayString
	ACCESS		read-only
	STATUS		mandatory
	DESCRIPTION	""
::= { device_var 2 }


temp_msg TRAP-TYPE
        ENTERPRISE device_var
        VARIABLES {deviceName,psAlarmString}
		DESCRIPTION ""
            ::= 1


END
