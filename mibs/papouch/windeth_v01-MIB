--*********************************
-- MIB table for WindETH sensor
--
-- by Miroslav Steiger
-- www.papouch.com - Copyright (c) 2016
--
--*********************************

windeth_v01-MIB DEFINITIONS ::= BEGIN

IMPORTS
--	MODULE-IDENTITY,
--	OBJECT-TYPE,
--	NOTIFICATION-TYPE,
		enterprises,
		IpAddress,
		Counter,
		Gauge,
		TimeTicks
    	FROM RFC1155-SMI
    OBJECT-TYPE
		FROM RFC-1212
	DisplayString
		FROM RFC1213-MIB
	TRAP-TYPE
		FROM RFC-1215
    ;

papouchProjekt	   OBJECT IDENTIFIER ::= { enterprises 18248 }
wind_eth		       OBJECT IDENTIFIER ::= { papouchProjekt 36 }
version1            OBJECT IDENTIFIER ::= { wind_eth 1 }

device_var         OBJECT IDENTIFIER ::= { version1 1 }
table_channel      OBJECT IDENTIFIER ::= { version1 2 }
table_watchValue   OBJECT IDENTIFIER ::= { version1 3 }
--
-- Type Definitions
--

PositiveInteger ::= INTEGER (0..65535)
---
--- TABULKA PRO PARAMETRY pro cteni a zapis
---
 channelTable OBJECT-TYPE
	SYNTAX  SEQUENCE OF ChannelEntry
	ACCESS  not-accessible
	STATUS  current
	DESCRIPTION	""
 ::= { table_channel 1 }
 channelEntry OBJECT-TYPE
	SYNTAX  ChannelEntry
	ACCESS  not-accessible
	STATUS  current
	DESCRIPTION	""
	INDEX   { index }
 ::= { channelTable 1 }
 ChannelEntry ::=
    SEQUENCE {
        inChStatus
            INTEGER,
        inChValue
            INTEGER,
--        inChUnits
--            INTEGER

    }

--
-- parametry pro cteni status mode
--
--
-- OID 1.3.6.1.4.1.18248.36.1.2.1.1.1.1 - 3
--
inChStatus  OBJECT-TYPE
	SYNTAX  	INTEGER
	ACCESS		read-only
	STATUS		current
	DESCRIPTION	"0 = OK, 1 = Not available, 2 = overflow, 3 = underflow, 4 = error (only for channel 1: 2 = over limit, 3 is not used)"
::= { channelEntry 1 }
--
-- OID 1.3.6.1.4.1.18248.36.1.2.1.1.2.1 - 3
--
inChValue  OBJECT-TYPE
	SYNTAX  	INTEGER
	ACCESS		read-only
	STATUS		current
	DESCRIPTION	""
::= { channelEntry 2 }


---
--- TABULKA PRO PARAMETRY HLIDANI
---
 watchValTable OBJECT-TYPE
	SYNTAX  SEQUENCE OF WatchValEntry
	ACCESS  not-accessible
	STATUS  current
	DESCRIPTION	""
 ::= { table_watchValue 1 }

 watchValEntry OBJECT-TYPE
	SYNTAX  WatchValEntry
	ACCESS  not-accessible
	STATUS  current
	DESCRIPTION	""
	INDEX   { index }
 ::= { watchValTable 1 }

WatchValEntry ::=
    SEQUENCE {
        modeWatch
            INTEGER,
        limitHi
            INTEGER,
        limitLo
            INTEGER,
--        limitHy
--            INTEGER
    }
--
-- OID 1.3.6.1.4.1.18248.36.1.3.1.1.1.1 - 3
--
modeWatch OBJECT-TYPE
	SYNTAX  	INTEGER(0..1)
	ACCESS		read-only
	STATUS		current
	DESCRIPTION	"1 = ON,0 = OFF"
::= { watchValEntry 1 }
--
-- OID 1.3.6.1.4.1.18248.36.1.3.1.1.2.1 - 3
--
limitHi OBJECT-TYPE
	SYNTAX  	INTEGER
	ACCESS		read-only
	STATUS		current
	DESCRIPTION	""
::= { watchValEntry 2 }
--
-- OID 1.3.6.1.4.1.18248.36.1.3.1.1.3.1 - 3
--
limitLo OBJECT-TYPE
	SYNTAX  	INTEGER
	ACCESS		read-only
	STATUS		current
	DESCRIPTION	""
::= { watchValEntry 3 }

--
-- OID 1.3.6.1.4.1.18248.36.1.1.1.0
--
deviceName OBJECT-TYPE
	SYNTAX		DisplayString
	ACCESS		read-only
	STATUS		mandatory
	DESCRIPTION	"Device Name"
::= { device_var 1 }
--
-- OID 1.3.6.1.4.1.18248.36.1.1.2.0
--
psAlarmString OBJECT-TYPE
	SYNTAX		DisplayString
	ACCESS		read-only
	STATUS		mandatory
	DESCRIPTION	""
::= { device_var 2 }


temp_msg TRAP-TYPE
        ENTERPRISE device_var
        VARIABLES {deviceName,psAlarmString}
		DESCRIPTION ""
            ::= 1

END
