--*********************************
-- MIB table for Papago ethernet meter
--
-- by Ing. Jiri Valek
-- www.papouch.com - Copyright (c) 2014
--
--*********************************

papago_dio_V01-MIB DEFINITIONS ::= BEGIN

IMPORTS
--	MODULE-IDENTITY,
--	OBJECT-TYPE,
--	NOTIFICATION-TYPE,
		enterprises,
		IpAddress,
		Counter,
		Gauge,
		TimeTicks
    	FROM RFC1155-SMI
    OBJECT-TYPE
		FROM RFC-1212
	DisplayString
		FROM RFC1213-MIB
	TRAP-TYPE
		FROM RFC-1215
    ;

papouchProjekt	   OBJECT IDENTIFIER ::= { enterprises 18248 }
papago_dio	       OBJECT IDENTIFIER ::= { papouchProjekt 33 }
version            OBJECT IDENTIFIER ::= { papago_dio 1 }

deviceVar         OBJECT IDENTIFIER ::= { version 1 }
in_table          OBJECT IDENTIFIER ::= { version 2 }
out_table         OBJECT IDENTIFIER ::= { version 3 }

--
-- Type Definitions
--
PositiveInteger ::= INTEGER (0..65535)
---
--- TABULKA VSTUPU, cteni a zapis
---
 inputsTable OBJECT-TYPE
	SYNTAX  SEQUENCE OF InputsEntry
	ACCESS  not-accessible
	STATUS  current
	DESCRIPTION	""
 ::= { in_table 1 }

 inputsEntry OBJECT-TYPE
	SYNTAX  InputsEntry
	ACCESS  not-accessible
	STATUS  current
	DESCRIPTION	""
	INDEX   { index }
 ::= { inputsTable 1 }

 InputsEntry ::=
    SEQUENCE {
        inState
            INTEGER,
        inCounter
            Counter,
        inDecNum
            INTEGER,
        inUnit
            DisplayString
    }
--
-- OID 1.3.6.1.4.1.18248.33.1.2.1.1.1.1 - x
-- Stav vstupu
--
inState  OBJECT-TYPE
	SYNTAX  	INTEGER
	ACCESS		read-only
	STATUS		current
	DESCRIPTION	"0 = OFF, 1 = ON"
::= { inputsEntry 1 }
--
-- OID 1.3.6.1.4.1.18248.33.1.2.1.1.2.1 - x
-- Hodnota citace
--
inCounter  OBJECT-TYPE
	SYNTAX  	Counter
	ACCESS		read-write
	STATUS		current
	DESCRIPTION	"Input counter (write=decrement)"
::= { inputsEntry 2 }
--
-- OID 1.3.6.1.4.1.18248.33.1.2.1.1.3.1 - x
-- Jednotka
--
inDecNum  OBJECT-TYPE
	SYNTAX  	INTEGER
	ACCESS		read-only
	STATUS		current
	DESCRIPTION	"Number of decimal places (0 - 3)"
::= { inputsEntry 3 }
--
-- OID 1.3.6.1.4.1.18248.33.1.2.1.1.4.1 - x
-- Pocet desetinnych mist
--
inUnit  OBJECT-TYPE
	SYNTAX  	DisplayString
	ACCESS		read-only
	STATUS		current
	DESCRIPTION	"String units"
::= { inputsEntry 4 }



---
--- TABULKA VYSTUPU, cteni a zapis
---
 outputsTable OBJECT-TYPE
	SYNTAX  SEQUENCE OF OutputsEntry
	ACCESS  not-accessible
	STATUS  current
	DESCRIPTION	""
 ::= { out_table 1 }

 outputsEntry OBJECT-TYPE
	SYNTAX  OutputsEntry
	ACCESS  not-accessible
	STATUS  current
	DESCRIPTION	""
	INDEX   { index }
 ::= { outputsTable 1 }

 OutputsEntry ::=
    SEQUENCE {
        outState
            INTEGER,
    }
--
-- OID 1.3.6.1.4.1.18248.33.1.3.1.1.1.1 - x
-- Stav vystupu
--
outState  OBJECT-TYPE
	SYNTAX  	INTEGER
	ACCESS		read-write
	STATUS		current
	DESCRIPTION	"0 = OFF, 1 = ON"
::= { outputsEntry 1 }


--
-- OID 1.3.6.1.4.1.18248.31.1.1.1.0
-- Název zarizeni
--
deviceName OBJECT-TYPE
	SYNTAX		DisplayString
	ACCESS		read-only
	STATUS		mandatory
	DESCRIPTION	"Device Name"
::= { deviceVar 1 }
--
-- OID 1.3.6.1.4.1.18248.31.1.1.2.0
-- Chybove hlaseni v trapu
--
psAlarmString OBJECT-TYPE
	SYNTAX		DisplayString
	ACCESS		read-only
	STATUS		mandatory
	DESCRIPTION	""
::= { deviceVar 2 }


watch_msg TRAP-TYPE
        ENTERPRISE deviceVar
        VARIABLES {deviceName,psAlarmString}
		DESCRIPTION ""
            ::= 1


END
