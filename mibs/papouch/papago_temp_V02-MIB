--*********************************
-- MIB table for Papago Ethernet meter
--
-- by Ing. Jiri Valek
-- www.papouch.com - Copyright (c) 2015
--
--*********************************

papago_temp_V02-MIB DEFINITIONS ::= BEGIN

IMPORTS
--	MODULE-IDENTITY,
--	OBJECT-TYPE,
--	NOTIFICATION-TYPE,
		enterprises,
		IpAddress,
		Counter,
		Gauge,
		TimeTicks
    	FROM RFC1155-SMI
    OBJECT-TYPE
		FROM RFC-1212
	DisplayString
		FROM RFC1213-MIB
	TRAP-TYPE
		FROM RFC-1215
    ;

papouchProjekt	   OBJECT IDENTIFIER ::= { enterprises 18248 }
papago_temp		   OBJECT IDENTIFIER ::= { papouchProjekt 31 }
version            OBJECT IDENTIFIER ::= { papago_temp 1 }

deviceVar         OBJECT IDENTIFIER ::= { version 1 }
tableChannel      OBJECT IDENTIFIER ::= { version 2 }
--
-- Type Definitions
--

PositiveInteger ::= INTEGER (0..65535)
---
--- TABULKA PRO PARAMETRY pro cteni a zapis
---
 channelTable OBJECT-TYPE
	SYNTAX  SEQUENCE OF ChannelEntry
	ACCESS  not-accessible
	STATUS  current
	DESCRIPTION	""
 ::= { tableChannel 1 }
 channelEntry OBJECT-TYPE
	SYNTAX  ChannelEntry
	ACCESS  not-accessible
	STATUS  current
	DESCRIPTION	""
	INDEX   { index }
 ::= { channelTable 1 }
 ChannelEntry ::=
    SEQUENCE {
		inChType
	        INTEGER,
        inChStatus
            INTEGER,
        inChValue
            INTEGER,
        inChUnits
            INTEGER

    }

-- OID 1.3.6.1.4.1.18248.31.1.2.1.1.1.1 - 6
-- Typ veliciny
--
inChType  OBJECT-TYPE
	SYNTAX  	INTEGER
	ACCESS		read-only
	STATUS		current
	DESCRIPTION	"0 = not used, 1 = temperature, 2 = humidity, 3 = dew point"
::= { channelEntry 1 }

--
-- OID 1.3.6.1.4.1.18248.31.1.2.1.1.2.1 - 6
-- Status kanalu
--
inChStatus  OBJECT-TYPE
	SYNTAX  	INTEGER
	ACCESS		read-only
	STATUS		current
	DESCRIPTION	"0 = OK,1 = Not available,2 = over-flow,3 = under-flow,4=ERR"
::= { channelEntry 2 }
--
-- OID 1.3.6.1.4.1.18248.31.1.2.1.1.3.1 - 6
-- Namerena hodnota
--
inChValue  OBJECT-TYPE
	SYNTAX  	INTEGER
	ACCESS		read-only
	STATUS		current
	DESCRIPTION	""
::= { channelEntry 3 }
--
-- OID 1.3.6.1.4.1.18248.31.1.2.1.1.4.1 - 6
-- Jednotka
--
inChUnits  OBJECT-TYPE
	SYNTAX  	INTEGER
	ACCESS		read-only
	STATUS		current
	DESCRIPTION	"Temperature and Dew point: 0 = Celsius, 1 = Fahrenfeit, 2 = Kelvin, Humidity: 0 = Percents"
::= { channelEntry 4 }
--
-- OID 1.3.6.1.4.1.18248.31.1.1.1.0
-- Název zarizeni
--
deviceName OBJECT-TYPE
	SYNTAX		DisplayString
	ACCESS		read-only
	STATUS		mandatory
	DESCRIPTION	"Device Name"
::= { deviceVar 1 }
--
-- OID 1.3.6.1.4.1.18248.31.1.1.2.0
-- Chybove hlaseni v trapu
--
psAlarmString OBJECT-TYPE
	SYNTAX		DisplayString
	ACCESS		read-only
	STATUS		mandatory
	DESCRIPTION	""
::= { deviceVar 2 }


temp_msg TRAP-TYPE
        ENTERPRISE deviceVar
        VARIABLES {deviceName,psAlarmString}
		DESCRIPTION ""
            ::= 1


END
