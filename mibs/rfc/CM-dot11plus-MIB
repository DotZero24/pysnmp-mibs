--
-- cmdot11plus MIB
--

CM-dot11plus-MIB DEFINITIONS ::= BEGIN

   IMPORTS
      enterprises, OBJECT-TYPE, MODULE-IDENTITY,
      Integer32, Unsigned32, IpAddress, Counter64
         FROM SNMPv2-SMI
      MacAddress, RowStatus, StorageType, TruthValue, DisplayString, PhysAddress
         FROM SNMPv2-TC
      ifIndex
      	 FROM IF-MIB             --  RFC 2863
      InetAddressType, InetAddress, InetPortNumber
         FROM INET-ADDRESS-MIB;

cmdot11plus MODULE-IDENTITY
      LAST-UPDATED "201406160000Z"  -- Jun 16, 2014
      ORGANIZATION
         "Motorola BCS"
      CONTACT-INFO
         "Author: Greg Nakanishi
          Org:    Motorola BCS
          postal: 6450 Sequence Drive
                  San Diego, CA 92121
          email:  gnakanishi@motorola.com
          phone:  858-404-2366"
      DESCRIPTION
          "This MIB defines additional 802.11 management objects not defined in the
          IEEE 802.11 MIB"

	REVISION  "201406120000Z"  -- Jun 12, 2014
      	DESCRIPTION
      	"Added by Tang Ho - OKCABLECPEMIB-434.
      	 - Added cmdot11WifiAcsdScanTimer
                 cmdot11WifiWMFEnable
                 cmdot11WifiBSEnable
                 cmdot11WifiATFEnable
                 cmdot11WifiTrafficSchedulerEnable
                 cmdot11WifiEbosEnable
                 cmdot11ACTxbfBFRCap
                 cmdot11ACTxbfBFECap
                 cmdot11BssOpmodeCapRequired"

	REVISION  "201406050000Z"  -- Jun 05, 2014
      	DESCRIPTION
      	"Added by Ananth Nayak - OKCABLECPEMIB-435.
      	 - Added cmdot11plusConnectedClientsTable
                     cmdot11plusConnectedClientsEntry
                     cmdot11plusClientIndex
                     cmdot11plusClientIpAddr
                     cmdot11plusClientID
                     cmdot11plusClientHostName
                     cmdot11plusClientAge
                     cmdot11plusClientMode
                     cmdot11plusClientRssi
                     cmdot11plusClientSpeed
                     cmdot11plusClientConnectedSSID"

	REVISION  "201308010000Z"  -- Aug 01, 2013
      DESCRIPTION
         "Added by Ryan Chen - OKCABLECPEMIB-426.
	      - Added cmdot11wifiHotspotMib
	      		cmdot11wifiHotspotEnabled
			cmdot11wifiHotspotTable
			cmdot11wifiHotspotIfEntry
				Cmdot11wifiHotspotIfEntry
					cmdot11wifiHotspotInstance
					cmdot11wifiHotspotIf
					cmdot11wifiHotspotMode
					cmdot11wifiHotspotCpeIdleTimeout
					cmdot11wifiHotspotCpeSessionTimeout
					cmdot11wifiHotspotRadiusAccAddressType
					cmdot11wifiHotspotRadiusAccAddress
					cmdot11wifiHotspotRadiusAccPort
					cmdot11wifiHotspotRadiusAccKey
					cmdot11wifiHotspotPacketFilterMask
					cmdot11wifiHotspotInsertDhcpOptionsMask
					cmdot11wifiHotspotRowStatus
			cmdot11wifiHotspotAutRateLimit
			cmdot11wifiHotspotAutDenialTimeout
			cmdot11wifiHotspotRadiusOrigIf
			cmdot11wifiHotspotIgnoreMaxCpeSetting
			cmdot11wifiHotspotDisablePMKCaching
			cmdot11wifiHotspotConnectionSpeedMin
			cmdot11wifiHotspotConnectionSpeedTimeout
	      - Added cmdot11l2ogreMib
	      		cmdot11l2ogreEnabled
			cmdot11l2ogrePriRemoteAddressType
			cmdot11l2ogrePriRemoteAddress
			cmdot11l2ogreSecRemoteAddressType
			cmdot11l2ogreSecRemoteAddress
			cmdot11l2ogreDSCP
			cmdot11l2ogreKeepAliveMode
			cmdot11l2ogreKeepAliveCount
			cmdot11l2ogreKeepAliveInterval
			cmdot11l2ogreKeepAliveFailureThreshold
			cmdot11l2ogreStatsTable
			cmdot11l2ogreStatsEntry
				Cmdot11l2ogreStatsEntry
					cmdot11l2ogreStatsIndex
					cmdot11l2ogreStatsBytesSent
					cmdot11l2ogreStatsBytesReceived
					cmdot11l2ogreStatsPacketsSent
					cmdot11l2ogreStatsPacketsReceived
					cmdot11l2ogreStatsDiscardPacketsReceived
					cmdot11l2ogreStatsErrorPacketsReceived
					cmdot11l2ogreStatsKeepAliveSent
					cmdot11l2ogreStatsKeepAliveReceived
			cmdot11l2ogreSourceIfTable
			cmdot11l2ogreSourceIfEntry
				Cmdot11l2ogreSourceIfEntry
					cmdot11l2ogreSourceIfInstance
					cmdot11l2ogreSourceIf
					cmdot11l2ogreSourceIfEnabled
					cmdot11l2ogreSourceIfVlanTag
					cmdot11l2ogreSourceIfMplsHeader
					cmdot11l2ogreSourceIfRowStatus
			cmdot11l2ogreOrigIf
			cmdot11l2ogreConcentratorServiceName
			cmdot11l2ogreDnsResolverRetryTimerMin
			cmdot11l2ogreDnsResolverRetryTimerMax."

	REVISION  "201212130000Z"  -- Dec 13, 2012
      	DESCRIPTION
         "Added by Tang He - OKCABLECPEMIB-405.
	      - Added cmdot11WifiApsScan and cmdot11WifiObssCoexMode to cmdot11BaseEntry Table
              - Added a new value mode54gOnly(2) and its description to mib cmdot11Wifi54gNetMode
              - Added a new value nOnly(3) and its description to mib cmdot11WifiNMode
              - Added a new value none(0) to mib cmdot11WifiNBandWidth
              - Added a new value none(0) and its description to mib cmdot11WifiNSideBand
              - Added ApsScanResults mibs (cmdot11ApsScanResultsTable):
                   - cmdot11Valid
                   - cmdot11NetworkName
                   - cmdot11SecurityMode
                   - cmdot11PhyMode
                   - cmdot11Rssi
                   - cmdot11Channel
                   - cmdot11MacAddress
              - Added AC interface mibs (cmdot1180211acInterfaceTable):
                   - cmdot11ACBandWidth
                   - cmdot11ACChannelSpec
              - Added cmdot11BssMaxAssociationsLimit to cmdot11BssEntry Table"

      REVISION  "201212130000Z"  -- Dec 13, 2012
      DESCRIPTION
         "Added by Richard DiBenedetto - OKCABLECPEMIB-397.
	      - Added ifIndex FROM IF-MIB to IMPORTS
	      - Updated to support Various Configuration File Editors."

	  REVISION  "201204100000Z"  -- April 10, 2012
      DESCRIPTION
         "Added by Jose Otero - OKCABLECPEMIB-361.
	      - Added cmdot11WifiChannelSetting to cmdot11BaseEntry Table
	      - changed cmdot11WifiCurrentChannel to read-only"

      REVISION  "201202230000Z"  -- Feb 23, 2012
      DESCRIPTION
         "Added by Jose Otero - cqvds00025699.
	      - Deprecated cmdot11MgmtBase. Objects are under cmdot11MgmtInterfaceTables
	        with support for dual Wifi Interfaces
	      - Edited description of cmdot11ResetToDefaults. Now under cmdot11MgmtInterfaceTables
	        with support for dual wifi interfaces.
	      - Added cmdot11MgmtInterfaceTables"


      REVISION  "201105240000Z"  -- May 24, 2011
      DESCRIPTION
         "Added by Uma and Kokila - cqvds00025699.
	      - Added MIB objects cmdot11plusDiag, cmdot11WlRevInfo"

      REVISION  "201006010000Z"  -- June 1, 2010
      DESCRIPTION
         "Added by Wilson from Compal broadband networks.
	      - Added MIB cqvds00022757
	      - cmdot11plusWps.
	      - cmdot11WpsEnable.
	      - cmdot11WpsMethod.
	      - cmdot11WpsPinNumber.
	      - cmdot11WpsAddClient."

      REVISION  "200911160000Z"  -- Nov 16, 2009
      DESCRIPTION
         "Added (cqvds00019448)by Uma and Mithun.
	      -Added MIB object cmdot11ResetToDefaults."

      REVISION  "200909090000Z"  -- Sep 09, 2009
      DESCRIPTION
	     "- Modified by P. Rajiv
          - Added MIB cqvds00018618.
          - cmdot11NMode, cmdot11NPhyRate, cmdot11NBand,
          - cmdot11NBandWidth, cmdot11NSideBand, and cmdot11NProtection."

      REVISION  "200908110000Z"  -- Aug 11, 2009
      DESCRIPTION
	     "- Modified (cqvds00016882) by Chen Yang.
          - Modified MIB object cmdot11BssSecurityMode.
          - Added (cqvds00016778)by Lisa Ruby.
	      - Added MIB object cmdot11MulticastRate."

      REVISION  "200905270000Z"  -- May 27, 2009
      DESCRIPTION
	     "Added (cqvds00015174)by Uma.
	      -Deprecated the MIB groups cmdot11plusMgmt and cmdot11plusBaseObjects.
		  -Changed the name of cmdot11plusMultipleSSID to cmdot11plusMgmtv2.
		  -Removed the statement 'This object is only valid for products that
		   support Multiple SSID' from description for MIB objects within the
		   group cmdot11plusMgmtv2.
		  -Added MIB group cmdot11MgmtBase
	      -Added MIB object cmdot11OperMode.
	      -Added MIB object cmdot11CurrentChannel.
	      -Added MIB object cmdot11ChannelSetting.
	      -Added MIB object cmdot1154gNetMode.
  	      -Added MIB object cmdot11BssWepSharedKeyAuthentication."


      REVISION  "200812190000Z"   -- Dec 19, 2008
      DESCRIPTION
        "Added (cqvds00012522)by Chen Yang , Poorna and Soumya.
         Added cmdot11BssWpaPasscode."

      REVISION  "200809110000Z"   -- Sep 11, 2008
      DESCRIPTION
        "Edited (cqvds00008397)by Chen Yang , Poorna and Soumya.
        Modified MIB in multiple SSID section.
        - Obsoleted the dot11BssNetworkBridge object.
        - Changed description for dot11BssSecurityMode."

      REVISION  "200402130000Z"
      DESCRIPTION
        "Edited by Carolyn Huynh.
        Published as cmdot11plus-11.mib.
        - Changed cmdot11plusWepPassPhrase range (8..31)
        "

      REVISION  "200310300000Z"
      DESCRIPTION
        "Edited by Jason Krasnow.
        Published as cmdot11plus-10.mib.
        - Added mib objects for WPA
        "


      REVISION  "200307150000Z"
      DESCRIPTION
        "Edited by Jason Krasnow.
        Published as cmdot11plus-09.mib.
        - Added mib object to control the tx output power in terms of percentage
        "

      REVISION  "200303030000Z"
      DESCRIPTION
        "Edited by Zheng Fang.
        Published as cmdot11plus-07.mib.
        - change cmdot11plusClosedNetworkEnable to cmdot11plusSsidBroadcastEnable.
        "

      REVISION  "200210080000Z"
      DESCRIPTION
        "Edited by Zheng Fang.
        Published as cmdot11plus-03.mib.
        - change cmdot11plusBasicRates default value to low,
        update cmdot11plusSetToFactory description,
        rename cmdot11plusWep128Enable to cmdot11plusWepMode to include disable value,
        add defval for cmdot11plusInterfaceEnable.
        "

      ::= {cm 51}


--
-- Path to root
--

gi OBJECT IDENTIFIER ::= {enterprises 1166}
giproducts OBJECT IDENTIFIER ::= {gi 1}
cm OBJECT IDENTIFIER ::= {giproducts 19}

-- Administrative assignments ----------------------

cmdot11plusObjects OBJECT IDENTIFIER ::= { cmdot11plus 1 }
cmdot11plusConformance OBJECT IDENTIFIER ::= { cmdot11plus 2 }
cmdot11wifiHotspotMib OBJECT IDENTIFIER ::= { cmdot11plus 3 }
cmdot11l2ogreMib OBJECT IDENTIFIER ::= { cmdot11plus 4 }

cmdot11plusMgmt OBJECT IDENTIFIER ::= { cmdot11plusObjects 1 }
cmdot11plusMgmtObjects OBJECT IDENTIFIER ::= { cmdot11plusMgmt 1 }

cmdot11plusBaseObjects OBJECT IDENTIFIER ::= { cmdot11plusObjects 2 }

cmdot11plusWpaObjects OBJECT IDENTIFIER ::= { cmdot11plusMgmt 2 }

cmdot11plusMgmtv2 OBJECT IDENTIFIER ::= { cmdot11plusObjects 5 }

cmdot11plusWps OBJECT IDENTIFIER ::= { cmdot11plusObjects 6 }

cmdot11plusDiag OBJECT IDENTIFIER ::= { cmdot11plusObjects 7 }

cmdot11wifiHotspotBase OBJECT IDENTIFIER ::= { cmdot11wifiHotspotMib 1 }

cmdot11l2ogreBase OBJECT IDENTIFIER ::= { cmdot11l2ogreMib 1 }

-- Object definitions ------------------------------
cmdot11plusSetToFactory OBJECT-TYPE
    SYNTAX      TruthValue
    MAX-ACCESS  read-write
    STATUS      deprecated
    DESCRIPTION
            "Setting this object to true(1) causes the dot11 plus default
            options to be returned back to factory defaults.
            Reading this object always returns false(2).

            The objects set to factory defaults are:

                  cmdot11plusInterfaceEnable,
                  cmdot11plusWepMode,
                  cmdot11plusAclEnable,
                  cmdot11plusSsidBroadcastEnable,
                  cmdot11plusBasicRates,
                  cmdot11plusShortPreambleEnable,
                  cmdot11plusPhyOperatingMode,
                  cmdot11plusTxOutputPower,
                  cmdot11plusWepPassPhrase,
                  cmdot11plusSecurityMode,
                  cmdot11plusWpaAuthMode,
                  cmdot11plusWpaGroupRekeyInterval,
                  cmdot11plusWpaEncryptionMode,
                  cmdot11plusLocalPreSharedKey,
                  cmdot11plusRemoteRadiusIpType,
                  cmdot11plusRemoteRadiusIp,
                  cmdot11plusRemoteRadiusPort,
                  cmdot11plusRemoteRadiusKey

            All entries in cmdot11plusWep128DefaultKeysTable and
            cmdot11plusAclTable will be destroyed.

            This MIB object is only valid for products supporting a single SSID
            "
    ::= { cmdot11plusBaseObjects 1 }

cmdot11plusInterfaceEnable OBJECT-TYPE
    SYNTAX      TruthValue
    MAX-ACCESS  read-write
    STATUS      deprecated
    DESCRIPTION
            "Setting this object to true(1) causes 802.11 interface to be enabled.
            Setting this object to false(2) causes 802.11 interface to be disabled.
            A change to this object takes effect only after the device is rebooted.

            This MIB object is only valid for products supporting a single SSID
            "
    DEFVAL { true }
    ::= { cmdot11plusBaseObjects 2 }

cmdot11plusApplySettings OBJECT-TYPE
    SYNTAX      TruthValue
    MAX-ACCESS  read-write
    STATUS      deprecated
    DESCRIPTION
        "When set to true(1),  all settings for 802.11 from this
		 MIB and from the ieee802dot11 MIB will be applied to
         the hardware for on-the-fly reconfiguration.
         Always returns false(2) when read.

         This MIB object is only valid for products supporting a single SSID
         "

    ::= { cmdot11plusBaseObjects 3 }

-- WEP configuration objects
cmdot11plusWepMode OBJECT-TYPE
      SYNTAX INTEGER
            {
                disable(1),
                bit64(2),
                bit128(3)
            }
      MAX-ACCESS read-write
      STATUS deprecated
      DESCRIPTION
         "The WEP encryption mode of 802.11 interface.

          This object is not writable and its return value should be ignored
          if cmdot11plusSecurityMode is not set to wep(2).

          This MIB object is only valid for products supporting a single SSID
          "
      DEFVAL { disable }
      ::= { cmdot11plusMgmtObjects 1 }

cmdot11plusWep128DefaultKeysTable OBJECT-TYPE
      SYNTAX SEQUENCE OF Cmdot11plusWep128DefaultKeysEntry
      MAX-ACCESS not-accessible
      STATUS deprecated
      DESCRIPTION
         "Table containing 128-bit WEP parameters.
          This table shall contain the four WEP default secret 128-bit key values
          corresponding to the four possible values.  The WEP default secret 128-bit
          keys are logically WRITE-ONLY.  Attempts to read the entries in this table
          shall return values of null.
          The default value of each WEP default key shall be null.

          This MIB object is only valid for products supporting a single SSID
          "
   ::= { cmdot11plusMgmtObjects 2 }

cmdot11plusWep128DefaultKeysEntry OBJECT-TYPE
      SYNTAX Cmdot11plusWep128DefaultKeysEntry
      MAX-ACCESS not-accessible
      STATUS deprecated
      DESCRIPTION
         "WEP key table entry. Each entry contains a 128-bit WEP key

         This MIB object is only valid for products supporting a single SSID
         "
      INDEX {cmdot11plusWep128Index}
   ::= { cmdot11plusWep128DefaultKeysTable 1 }

Cmdot11plusWep128DefaultKeysEntry ::=
      SEQUENCE {
         cmdot11plusWep128Index
            Integer32,
         cmdot11plusWep128DefaultKeyValue
            OCTET STRING
       }

cmdot11plusWep128Index OBJECT-TYPE
      SYNTAX Integer32 (1..4)
      MAX-ACCESS not-accessible
      STATUS deprecated
      DESCRIPTION
         "Identifies instances of the columnar objects in the ACL table

          This MIB object is only valid for products supporting a single SSID
         "
      ::= { cmdot11plusWep128DefaultKeysEntry 1 }

cmdot11plusWep128DefaultKeyValue OBJECT-TYPE
      SYNTAX OCTET STRING (SIZE(13))
      MAX-ACCESS read-create
      STATUS deprecated
      DESCRIPTION
         "A 128-bit WEP default secret key value.

         This MIB object is only valid for products supporting a single SSID
         "
      ::= { cmdot11plusWep128DefaultKeysEntry 2 }

-- MAC ACL configuration objects

cmdot11plusAclEnable OBJECT-TYPE
      SYNTAX TruthValue
      MAX-ACCESS read-write
      STATUS deprecated
      DESCRIPTION
         "This object controls whether MAC address ACL checking is enabled in the access point.
          When 'true', AP allows only those stations listed in cmdot11plusAclTable to associate.
          When 'false', AP allows any station to associate.

          This MIB object is only valid for products supporting a single SSID
          "
      DEFVAL { false }
      ::= { cmdot11plusMgmtObjects 3 }

cmdot11plusAclTable OBJECT-TYPE
      SYNTAX SEQUENCE OF Cmdot11plusAclEntry
      MAX-ACCESS not-accessible
      STATUS deprecated
      DESCRIPTION
         "MAC ACL table contains a list of MAC addresses for stations that are allowed to
          associate with the access point.

          This MIB object is only valid for products supporting a single SSID
          "
   ::= { cmdot11plusMgmtObjects 4 }

cmdot11plusAclEntry OBJECT-TYPE
      SYNTAX Cmdot11plusAclEntry
      MAX-ACCESS not-accessible
      STATUS deprecated
      DESCRIPTION
         "MAC ACL table entry. Primary column of the entry is the MAC address.

         This MIB object is only valid for products supporting a single SSID
         "
      INDEX {cmdot11plusAclIndex}
   ::= { cmdot11plusAclTable 1 }

Cmdot11plusAclEntry ::=
      SEQUENCE {
         cmdot11plusAclIndex
            Integer32,
         cmdot11plusAclAddress
            MacAddress,
         cmdot11plusAclRowStatus
            RowStatus
         }

cmdot11plusAclIndex OBJECT-TYPE
      SYNTAX Integer32 (1..32)
      MAX-ACCESS not-accessible
      STATUS deprecated
      DESCRIPTION
         "Identifies instances of the columnar objects in the ACL table

         This MIB object is only valid for products supporting a single SSID
         "
      ::= { cmdot11plusAclEntry 1 }

cmdot11plusAclAddress OBJECT-TYPE
      SYNTAX MacAddress
      MAX-ACCESS read-create
      STATUS deprecated
      DESCRIPTION
         "A MAC address of a station that is allowed to associate with the access point.

         This MIB object is only valid for products supporting a single SSID
         "
      ::= { cmdot11plusAclEntry 2 }

cmdot11plusAclRowStatus OBJECT-TYPE
    SYNTAX      RowStatus
    MAX-ACCESS  read-create
    STATUS      deprecated
    DESCRIPTION
       "The RowStatus interlock for creation and deletion.

       This MIB object is only valid for products supporting a single SSID
       "
    ::= { cmdot11plusAclEntry 3 }

cmdot11plusSsidBroadcastEnable OBJECT-TYPE
      SYNTAX TruthValue
      MAX-ACCESS read-write
      STATUS deprecated
      DESCRIPTION
         "When 'true', AP does broadcast SSID in beacon packets.
          When 'false', AP does not broadcast SSID in beacon packets.

          This MIB object is only valid for products supporting a single SSID
          "

      DEFVAL { true }
      ::= { cmdot11plusMgmtObjects 5 }

-- Basic rate configuration

cmdot11plusBasicRates OBJECT-TYPE
      SYNTAX INTEGER
        {
         low(1),   -- 1 & 2 Mbps
         high(2)   -- 1, 2, 5.5, & 11 Mbps
        }
      MAX-ACCESS read-write
      STATUS deprecated
      DESCRIPTION
         "Set of data rates that all stations in a BSS must be capable of receiving.

         This MIB object is only valid for products supporting a single SSID
         "
      DEFVAL { low }
      ::= { cmdot11plusMgmtObjects 6 }

-- Short Preamble Enable configuration

cmdot11plusShortPreambleEnable OBJECT-TYPE
      SYNTAX TruthValue
      MAX-ACCESS read-write
      STATUS deprecated
      DESCRIPTION
         "When 'true', AP tranamits packets using a short preamble.
          When 'false', AP transmits packets with the standard long preamble.

          This MIB object is only valid for products supporting a single SSID
          "

      DEFVAL { false }
      ::= { cmdot11plusMgmtObjects 7 }

-- Counters Reset configuration

cmdot11plusCountersReset OBJECT-TYPE
      SYNTAX TruthValue
      MAX-ACCESS read-write
      STATUS deprecated
      DESCRIPTION
         "Setting this object to true(1) resets the counters in dot11CountersTable.
          Reading this object always returns false(2).

          This MIB object is only valid for products supporting a single SSID
          "
      ::= { cmdot11plusMgmtObjects 8 }

-- 802.11g Operating Mode

cmdot11plusPhyOperatingMode OBJECT-TYPE
      SYNTAX INTEGER
        {
         standard(1),  -- 11b/11g Standard
         enhanced(2)   -- 11g Enhanced
        }
      MAX-ACCESS read-write
      STATUS deprecated
      DESCRIPTION
         "This is the supported wireless operating mode of the SBG.
          Select the default 11b/11g standard(1) option for most cases as this is the
          most flexible mode. It allows both 802.11b and 802.11g stations to work
          with the SBG device.  Select the 11g enhanced(2) option only if all
          802.11g stations in use are compatible with the performance enhancing
          features of the 11g Enhanced mode. Note: 11g enhanced is a proprietary
          mode which is not supported by all 802.11g stations.

          This MIB object is only valid for products supporting a single SSID
          "
      DEFVAL { standard }
      ::= { cmdot11plusMgmtObjects 9 }

cmdot11plusTxOutputPower OBJECT-TYPE
      SYNTAX INTEGER (100 | 75 | 50 | 25 | 12 | 6 | 3)
      MAX-ACCESS read-write
      STATUS deprecated
      DESCRIPTION
         "This object controls the ouput power of the 802.11 transmitter.  The number
          is a percentage of the maximum power possible based on 802.11 technology
          and other board specific issues.

          This MIB object is only valid for products supporting a single SSID
          "
      DEFVAL { 100 }
      ::= { cmdot11plusMgmtObjects 10 }

cmdot11plusWepPassPhrase OBJECT-TYPE
    SYNTAX      DisplayString (SIZE(8..31))
    MAX-ACCESS  read-write
    STATUS      deprecated
    DESCRIPTION
        "Controls and reflects the WEP pass phrase.

        This MIB object is only valid for products supporting a single SSID
        "
    ::= { cmdot11plusMgmtObjects 11 }

cmdot11plusGenerateWepKeys OBJECT-TYPE
    SYNTAX      TruthValue
    MAX-ACCESS  read-write
    STATUS      deprecated
    DESCRIPTION
        "Applies the WEP PassPhrase by generating new keys from the string
         set in cmdot11plusWepPassPhrase. The keys are generated using the
         algorithm described in 802.11i appendix F.  This object will always
         return false went read.

         This MIB object is only valid for products supporting a single SSID
         "
    ::= { cmdot11plusMgmtObjects 12 }

cmdot11plusSecurityMode OBJECT-TYPE
    SYNTAX      INTEGER {
                none(1),
                wep(2),
                wpa(3)
    }
    MAX-ACCESS  read-write
    STATUS      deprecated
    DESCRIPTION
        "Sets the network authentication and/or security method.
         WEP requires cmdot11plusWepMode to be set to either 64bit or 128bit
         encryption and valid keys be entered.
         WPA requires either valid RADIUS parameters be set or
         a valid WPA Pre-Shared Key to be set.

         This MIB object is only valid for products supporting a single SSID
         "
    DEFVAL { none }
    ::= { cmdot11plusMgmtObjects 13 }

cmdot11plusWpaAuthMode OBJECT-TYPE
    SYNTAX      INTEGER {
                local(1),
                remote(2)
                }
    MAX-ACCESS  read-write
    STATUS      deprecated
    DESCRIPTION
        "Sets the network authentication method to be used with WPA.
         Local(1) requires a valid WPA Pre-Shared Key to be set. This
		 mode is sometimes called WPA-PSK.
         Remote(2) requires valid RADIUS parameters be set.  This mode
		 is sometimes called WPA with 802.1x authentication.

         This object is not writable and its return value should be ignored
         if cmdot11plusSecurityMode is not set to wpa(3).

         This MIB object is only valid for products supporting a single SSID
         "
    DEFVAL { local }
    ::= { cmdot11plusWpaObjects 1 }

cmdot11plusWpaGroupRekeyInterval OBJECT-TYPE
    SYNTAX      Unsigned32
    UNITS       "seconds"
    MAX-ACCESS  read-write
    STATUS      deprecated
    DESCRIPTION
        "Sets the WPA Group Rekey Interval in seconds. Set to zero to disable
         periodic rekeying.

         This MIB object is only valid for products supporting a single SSID
         "
DEFVAL { 300 }
    ::= { cmdot11plusWpaObjects 2 }

cmdot11plusWpaEncryptionMode OBJECT-TYPE
    SYNTAX      INTEGER {
                tkip(1),
                aes(2)
                }
    MAX-ACCESS  read-write
    STATUS      deprecated
    DESCRIPTION
        "TKIP (Temporal Key Integrity Protocol) provides data encryption enhancements
         including a per-packet key mixing function, a MIC, an IV(initialization vector)
         and a re-keying mechanism.

         AES (Advanced Encryption Standard) algorithm implements symmetric key
         cryptography as a block cipher using 128-bit keys.

         This object is not writable and its return value should be ignored
         if cmdot11plusSecurityMode is not set to wpa(3).

         This MIB object is only valid for products supporting a single SSID
         "
    DEFVAL { tkip }
    ::= { cmdot11plusWpaObjects 3 }

cmdot11plusLocalPreSharedKey OBJECT-TYPE
    SYNTAX      OCTET STRING (SIZE(8..63))
    MAX-ACCESS  read-write
    STATUS      deprecated
    DESCRIPTION
        "Sets the WPA Pre-Shared Key (PSK).  This value MUST a
         8 to 63 character ASCII string.

         This MIB object is only valid for products supporting a single SSID
         "
    ::= { cmdot11plusWpaObjects 4 }

cmdot11plusRemoteRadiusIpType OBJECT-TYPE
    SYNTAX      InetAddressType
    MAX-ACCESS  read-write
    STATUS      deprecated
    DESCRIPTION
        "The address type assigned for the Radius IP address

        This MIB object is only valid for products supporting a single SSID
        "
    DEFVAL { ipv4 }
    ::= { cmdot11plusWpaObjects 5 }

cmdot11plusRemoteRadiusIp OBJECT-TYPE
    SYNTAX      OCTET STRING (SIZE(0..128))
    MAX-ACCESS  read-write
    STATUS      deprecated
    DESCRIPTION
        "Sets RADIUS server address.  The type of address is determined by
         cmdot11plusRemoteRadiusIpType.  If it is ipv4 then this should
         be set to the 4 octets representing the IP address.  If it is
         a DNS name then this must be a FQDN in ascii.

         This MIB object is only valid for products supporting a single SSID
         "
    ::= { cmdot11plusWpaObjects 6 }

cmdot11plusRemoteRadiusPort OBJECT-TYPE
    SYNTAX      InetPortNumber
    MAX-ACCESS  read-write
    STATUS      deprecated
    DESCRIPTION
        "Sets the UDP port used to communicate with the RADIUS server.

        This MIB object is only valid for products supporting a single SSID
        "
    DEFVAL { 1812 }
    ::= { cmdot11plusWpaObjects 7 }

cmdot11plusRemoteRadiusKey OBJECT-TYPE
    SYNTAX      OCTET STRING (SIZE(0..255))
    MAX-ACCESS  read-write
    STATUS      deprecated
    DESCRIPTION
        "Sets or displays the RADIUS key.

        This MIB object is only valid for products supporting a single SSID
        "
    ::= { cmdot11plusWpaObjects 8 }





-- Conformance
cmdot11plusCompliances OBJECT IDENTIFIER ::= { cmdot11plusConformance 1 }
cmdot11plusGroups      OBJECT IDENTIFIER ::= { cmdot11plusConformance 2 }

-- Compliance statements
cmdot11plusCompliance MODULE-COMPLIANCE
    STATUS       deprecated
    DESCRIPTION "The compliance statement for access points that implement the
                 cmdot11plus MIB

                 This MIB object is only valid for products supporting a single SSID
                 "

    MODULE       -- this module
        MANDATORY-GROUPS { cmdot11plusBaseGroup }

    ::= { cmdot11plusCompliances 1 }

-- Units of compliance
cmdot11plusBaseGroup OBJECT-GROUP
    OBJECTS     {
                  cmdot11plusSetToFactory,
                  cmdot11plusInterfaceEnable,
                  cmdot11plusWepMode,
                  cmdot11plusWep128DefaultKeyValue,
                  cmdot11plusAclEnable,
                  cmdot11plusAclAddress,
                  cmdot11plusAclRowStatus,
                  cmdot11plusSsidBroadcastEnable,
                  cmdot11plusCountersReset,
                  cmdot11plusTxOutputPower,
                  cmdot11plusWepPassPhrase,
                  cmdot11plusGenerateWepKeys,
                  cmdot11plusSecurityMode,
				  cmdot11plusApplySettings
                }
    STATUS       deprecated
    DESCRIPTION "A collection of the basic objects providing for configuration
                 of additional 802.11 management objects not defined
                 by the IEEE 802.11 MIB.

                 This MIB object is only valid for products supporting a single SSID
                 "
    ::= { cmdot11plusGroups 1 }

cmdot11BplusGroup OBJECT-GROUP
    OBJECTS     {
                  cmdot11plusBasicRates,
                  cmdot11plusShortPreambleEnable
                }
    STATUS       deprecated
    DESCRIPTION "A collection of objects providing for configuration
                 of additional 802.11 management objects for 802.11b
                 operation.

                 This MIB object is only valid for products supporting a single SSID
                 "
    ::= { cmdot11plusGroups 2 }

cmdot11GplusGroup OBJECT-GROUP
    OBJECTS     {
                  cmdot11plusPhyOperatingMode,
                  cmdot11plusWpaEncryptionMode
                }
    STATUS       deprecated
    DESCRIPTION "A collection of objects providing for configuration
                 of additional 802.11 management objects for 802.11g
                 operation.

                 This MIB object is only valid for products supporting a single SSID
                 "
    ::= { cmdot11plusGroups 3 }


cmdot11plusWpaGroup OBJECT-GROUP
    OBJECTS     {
                  cmdot11plusWpaAuthMode,
                  cmdot11plusWpaGroupRekeyInterval,
                  cmdot11plusLocalPreSharedKey,
                  cmdot11plusRemoteRadiusIpType,
                  cmdot11plusRemoteRadiusIp,
                  cmdot11plusRemoteRadiusPort,
                  cmdot11plusRemoteRadiusKey
                }
    STATUS       deprecated
    DESCRIPTION "A collection of objects providing for configuration
                 of additional 802.11 management objects for WPA
                 operation.

                 This MIB object is only valid for products supporting a single SSID
                 "
    ::= { cmdot11plusGroups 4 }



cmdot11MgmtBase OBJECT IDENTIFIER ::= { cmdot11plusMgmtv2 1 }

cmdot11OperMode OBJECT-TYPE
    SYNTAX      INTEGER
    			{
                 enable(1),
                 disable(2)
                }
    MAX-ACCESS  read-write
    STATUS      deprecated
    DESCRIPTION
        "Setting this object to enable(1) enables the Wireless interface. Setting this object to
         disable(2) disables the Wireless interface.
        "
    ::= { cmdot11MgmtBase 1 }

cmdot11CurrentChannel OBJECT-TYPE
    SYNTAX      Unsigned32
    MAX-ACCESS  read-only
    STATUS      deprecated
    DESCRIPTION
        "Reading this object displays the current channel number the access point is operating in.
         It displays 0 if the Wireless interface is disabled.
        "
    ::= { cmdot11MgmtBase 2 }

cmdot11ChannelSetting  OBJECT-TYPE
    SYNTAX      Unsigned32 (0..216)
    MAX-ACCESS  read-write
    STATUS      deprecated
    DESCRIPTION
        "This object sets the current channel number (802.11g) or control
        channel (802.11n).

         If set to (0), the AP will be put in auto-channel mode where
	 it automatically scans for the least-crowded channel.

         For 802.11g cards, available channels are 1-14.
	 For 802.11n cards, available channels are 34-216.

         Channel selection is also subject to restrictions based on the selected
	 country code.
	    "
    ::= { cmdot11MgmtBase 3 }

cmdot1154gNetMode OBJECT-TYPE
    SYNTAX      INTEGER {
		mode54g11bOnly(0),
		mode54gAuto(1),
		mode54gPerformance(4),
		mode54gLRS(5)
    }
    MAX-ACCESS  read-write
    STATUS      deprecated
    DESCRIPTION
        "Controls and reflects the behavior of the device with regards to which
         802.11 mode is used.  If set to mode54gLRS(5), the device
         will interoperate with the widest variety of 54g and 802.11b clients.
         If set to mode54gPerformance(4), the highest throughput will be provided
         and only 54g clients will be accepted, however nearby 802.11b networks
         may suffer degraded performance.  If set to mode54g11bOnly(0), only 802.11b clients
	     will be accepted.  If set to mode54gAuto(1) the device will attempt to operate
	     at 54g rates unless an 802.11b client is detected.
	    "
    ::= { cmdot11MgmtBase 10 }

cmdot11NMode OBJECT-TYPE
    SYNTAX      INTEGER {
        auto(1),
        off(2)
    }
    MAX-ACCESS  read-write
    STATUS      deprecated
    DESCRIPTION
            "Used to enable/disable 802.11n operation.
            'Auto' is used to enable 802.11n operation; the Access Point will detect which
             stations are out there and operate in the proper mode.
            'Off' is used to disable 802.11n operation; the Access Point will operate in the
             mode specified by dot1154gNetMode.
             Note: This MIB object is only valid for products supporting 802.11n,
             and also affects other MIB selections."
    ::= { cmdot11MgmtBase 16 }

cmdot11NPhyRate OBJECT-TYPE
    SYNTAX      INTEGER {
        auto(0),
        legacy(1),
        mcs0(2),
        mcs1(3),
        mcs2(4),
        mcs3(5),
        mcs4(6),
        mcs5(7),
        mcs6(8),
        mcs7(9),
        mcs8(10),
        mcs9(11),
        mcs10(12),
        mcs11(13),
        mcs12(14),
        mcs13(15),
        mcs14(16),
        mcs15(17)
    }
    MAX-ACCESS  read-write
    STATUS      deprecated
    DESCRIPTION
            "Used to specify the 802.11n PHY transmission rate.
            'Auto' is used to allow the Access Point to dynamically adapt
            to the environment and transmit using the fastest data rate
            for the given environmental conditions.
            'Legacy' is used to restrict the transmission to 802.11b/g rates.
            'mcs0' through 'mcs15' are used to force the 802.11N PHY transmission
            rate for the Access Point to a particular speed. The MCS-to-speed mapping
            is provided by the 802.11n spec and depends on whether a 20 MHz
            channel or a 40 MHz channel is being used.
            Note: This MIB object is only valid for products supporting 802.11n."
    ::= { cmdot11MgmtBase 17 }


cmdot11NBand OBJECT-TYPE
    SYNTAX      INTEGER {
        band-2-4G(1),
        band-5G(2)
    }
    MAX-ACCESS  read-write
    STATUS      deprecated
    DESCRIPTION
            "Selects the wireless frequency band (2.4 GHz or 5 GHz) the Access Point will operate in.
            Note: This MIB object is only valid for products supporting 802.11n."
    ::= { cmdot11MgmtBase 18 }

cmdot11NBandWidth OBJECT-TYPE
    SYNTAX      INTEGER {
        width-20MHz(1),
        width-20-40MHz(2)
    }
    MAX-ACCESS  read-write
    STATUS      deprecated
    DESCRIPTION
            "Specifies the channel width (20 MHz or 20/40 MHz) to be used by the Access Point.
            When 20/40MHz is selected 802.11n clients experience improved throughput
            using 40 MHz, while legacy clients(either 802.11a or 802.11b/g) can
            still be serviced without interruption using 20MHz.
            Note: This MIB object is only valid for products supporting 802.11n, and
            also affects other MIB selections such as cmdot11NSideBand."
    ::= { cmdot11MgmtBase 19 }

cmdot11NSideBand OBJECT-TYPE
    SYNTAX      INTEGER {
        upper(1),
        lower(2)
    }
    MAX-ACCESS  read-write
    STATUS      deprecated
    DESCRIPTION
            "When bonded channels (40 MHz) are used this object specifies if the
             control (primary) channel is in the lower or upper 20 MHz band of the
             bonded 40 MHz channel.
             Note: This MIB object is only valid for products supporting 802.11n and
             only applies when cmdot11NBandWidth is set to 20/40MHz."
    ::= { cmdot11MgmtBase 20 }

cmdot11NProtection OBJECT-TYPE
    SYNTAX      INTEGER {
        auto(1),
        off(2)
    }
    MAX-ACCESS  read-write
    STATUS      deprecated
    DESCRIPTION
            "Determines if protection will be turned on or off for 802.11n mode.
             When set to auto, the Access Point will enable protection to allow
             802.11n clients to co-exist with 802.11a/b/g clients.
             Note: This MIB object is only valid for products supporting 802.11n."
    ::= { cmdot11MgmtBase 21 }


cmdot11MulticastRate OBJECT-TYPE
    SYNTAX      INTEGER {
            rateAuto(1),
            rate1Mbps(2),
            rate2Mbps(3),
            rate5dot5Mbps(4),
            rate6Mbps(5),
            rate9Mbps(6),
            rate11Mbps(7),
            rate12Mbps(8),
            rate18Mbps(9),
            rate24Mbps(10),
            rate36Mbps(11),
            rate48Mbps(12),
            rate54Mbps(13)
	}
    MAX-ACCESS  read-write
    STATUS      deprecated
    DESCRIPTION
            "Controls the physical layer transmission rate used for Multicast traffic on the
             Wireless interface. The defined rates are the theoretical physical link rate.
             Actual data rates will be much lower due to PHY and MAC overhead. If rateAuto
             is selected, the Wireless driver will select the lowest valid rate,
             which for 802.11b and 802.11g is 1Mbps.
             Note: Values above 11Mbps are not valid for 802.11b. If cmdot1154gNetMode is set
             to mode54g11bOnly and this object is set to a value above 11Mbps, the set will be rejected."
    ::= { cmdot11MgmtBase 100 }



cmdot11MgmtInterfaceTables OBJECT IDENTIFIER ::= { cmdot11plusMgmtv2 2}

cmdot11BaseTable  OBJECT-TYPE
    SYNTAX      SEQUENCE OF Cmdot11BaseEntry
    MAX-ACCESS  not-accessible
    STATUS      current
    DESCRIPTION
        "A table of settings used to configure the primary wi-fi interfaces belonging to multiple wi-fi instances."
    ::= { cmdot11MgmtInterfaceTables  1 }

cmdot11BaseEntry OBJECT-TYPE
    SYNTAX      Cmdot11BaseEntry
    MAX-ACCESS  not-accessible
    STATUS      current
    DESCRIPTION
        "An entry describing the configuration of a primary wi-fi interface.

         An entry exists in this table for each entry in the ifTable with an
         ifType value of ieee80211(71), and which is designated as a primary
         wi-fi interface.

         Note that non-primary interfaces (such as Guest Network interfaces) are not represented in this table."
    INDEX   { ifIndex }
    ::= { cmdot11BaseTable   1 }

Cmdot11BaseEntry ::=
    SEQUENCE    {
        cmdot11WifiOperMode            INTEGER,
        cmdot11WifiCurrentChannel      Unsigned32,
        cmdot11WifiBeaconInterval      Unsigned32,
        cmdot11WifiDTIMInterval        Unsigned32,
        cmdot11WifiFragThresh          Unsigned32,
        cmdot11WifiRTSThresh           Unsigned32,
        cmdot11WifiShortRetryLimit     Unsigned32,
        cmdot11WifiLongRetryLimit      Unsigned32,
        cmdot11WifiMulticastRate       INTEGER,
        cmdot11WifiOutputPower         INTEGER,
        cmdot11WifiResetToDefaults     TruthValue,
        cmdot11WifiChannelSetting      Unsigned32,
	cmdot11WifiApsScan	       TruthValue,
	cmdot11WifiObssCoexMode	       TruthValue,
        cmdot11WifiAcsdScanTimer       Unsigned32,
        cmdot11WifiWMFEnable	       TruthValue,
        cmdot11WifiBSEnable            TruthValue,
        cmdot11WifiATFEnable           TruthValue,
        cmdot11WifiTrafficSchedulerEnable    TruthValue,
        cmdot11WifiEbosEnable	    TruthValue
    }

cmdot11WifiOperMode OBJECT-TYPE
    SYNTAX      INTEGER {
                 enable(1),
                 disable(2)
    }
    MAX-ACCESS  read-write
    STATUS      current
    DESCRIPTION
        "Setting this object to enable(1) enables the Wireless interface. Setting this object to
         disable(2) disables the Wireless interface."
    ::= { cmdot11BaseEntry 1 }

-- 'Basic' web page objects

cmdot11WifiCurrentChannel OBJECT-TYPE
    SYNTAX      Unsigned32 (0..216)
    MAX-ACCESS  read-only
    STATUS      current
    DESCRIPTION
        "Reflects the current channel number (802.11g) or
	     control channel (802.11n) for this interface.

         For 802.11g cards, available channels are 1-14.
	     For 802.11n cards, available channels are 34-216.

         Channel selection is also subject to restrictions based on the selected
	     country code."
    ::= { cmdot11BaseEntry 2 }

-- 'Advanced' web page objects

cmdot11WifiBeaconInterval OBJECT-TYPE
    SYNTAX      Unsigned32  (0..65535)
    UNITS       "milliseconds"
    MAX-ACCESS  read-write
    STATUS      current
    DESCRIPTION
        "Controls and reflects the beacon interval for this interface."
    ::= { cmdot11BaseEntry 3 }

cmdot11WifiDTIMInterval OBJECT-TYPE
    SYNTAX      Unsigned32  (1..255)
    UNITS       "milliseconds"
    MAX-ACCESS  read-write
    STATUS      current
    DESCRIPTION
        "Controls and reflects the DTIM interval for this interface."
    ::= { cmdot11BaseEntry 4 }

cmdot11WifiFragThresh OBJECT-TYPE
    SYNTAX      Unsigned32  (256..2346)
    UNITS       "bytes"
    MAX-ACCESS  read-write
    STATUS      current
    DESCRIPTION
        "Controls and reflects the fragmentation threshold for this interface."
    ::= { cmdot11BaseEntry 5 }

cmdot11WifiRTSThresh OBJECT-TYPE
    SYNTAX      Unsigned32  (0..2347)
    MAX-ACCESS  read-write
    STATUS      current
    DESCRIPTION
        "Controls and reflects the RTS threshold for this interface."
    ::= { cmdot11BaseEntry 6 }

-- Short and Long Retry Limit not on the web page, but presented here.

cmdot11WifiShortRetryLimit OBJECT-TYPE
    SYNTAX      Unsigned32  (1..255)
    MAX-ACCESS  read-write
    STATUS      current
    DESCRIPTION
        "Controls and reflects the short retry limit for this interface."
    ::= { cmdot11BaseEntry 7 }

cmdot11WifiLongRetryLimit OBJECT-TYPE
    SYNTAX      Unsigned32  (1..255)
    MAX-ACCESS  read-write
    STATUS      current
    DESCRIPTION
        "Controls and reflects the long retry limit for this interface."
    ::= { cmdot11BaseEntry 8 }

cmdot11WifiMulticastRate OBJECT-TYPE
    SYNTAX      INTEGER {
            rateAuto(1),
            rate1Mbps(2),
            rate2Mbps(3),
            rate5dot5Mbps(4),
            rate6Mbps(5),
            rate9Mbps(6),
            rate11Mbps(7),
            rate12Mbps(8),
            rate18Mbps(9),
            rate24Mbps(10),
            rate36Mbps(11),
            rate48Mbps(12),
            rate54Mbps(13)
    }
    MAX-ACCESS  read-write
    STATUS      current
    DESCRIPTION
            "Controls the physical layer transmission rate used for Multicast traffic on the
             Wireless interface. The defined rates are the theoretical physical link rate.
             Actual data rates will be much lower due to PHY and MAC overhead. If rateAuto
             is selected, the Wireless driver will select the lowest valid rate,
             which for 802.11b and 802.11g is 1Mbps.
             Note: Values above 11Mbps are not valid for 802.11b. If cmdot1154gNetMode is set
             to mode54g11bOnly and this object is set to a value above 11Mbps, the set will be rejected."
    DEFVAL { rateAuto }
    ::= { cmdot11BaseEntry 9 }

cmdot11WifiOutputPower OBJECT-TYPE
    SYNTAX      INTEGER {
                percent25(25),
                percent50(50),
                percent75(75),
                percent100(100)
    }
    MAX-ACCESS  read-write
    STATUS      current
    DESCRIPTION
        "Sets the output power relative to the hardware's maximum capability."
    DEFVAL { percent100 }
    ::= { cmdot11BaseEntry 10 }

cmdot11WifiResetToDefaults OBJECT-TYPE
    SYNTAX      TruthValue
    MAX-ACCESS  read-write
    STATUS      current
    DESCRIPTION
        "Setting this object to true(1) causes all the wireless settings
         including primary and Guest Network settings for a particular wi-fi instance to be reset to factory defaults.
         Reading this object always returns false(2)."
    ::= { cmdot11BaseEntry 11 }

cmdot11WifiChannelSetting OBJECT-TYPE
    SYNTAX      Unsigned32 (0..216)
    MAX-ACCESS  read-write
    STATUS      current
    DESCRIPTION
        "Controls and reflects the current channel number (802.11g) or
	     control channel (802.11n) for this interface.

         If set to (0), the AP will be put in auto-channel mode where
	     it automatically scans for the least-crowded channel.

         For 802.11g cards, available channels are 1-14.
	     For 802.11n cards, available channels are 34-216.

         Channel selection is also subject to restrictions based on the selected
	     country code."
    ::= { cmdot11BaseEntry 12 }

cmdot11WifiApsScan OBJECT-TYPE
    SYNTAX      TruthValue
    MAX-ACCESS  read-write
    STATUS      current
    DESCRIPTION
        "If set to true(1), the Wi-Fi Radio will be configured to scan for APs.
        Scan results with a list of neighboring APs will be updated in cmdot11ApsScanResultsTable.
        Always returns false(2) when read."
    ::= { cmdot11BaseEntry 13 }

cmdot11WifiObssCoexMode OBJECT-TYPE
    SYNTAX      TruthValue
    MAX-ACCESS  read-write
    STATUS      current
    DESCRIPTION
        "Controls and reflects the state of the Wi-Fi Radio's OBSS Coexistence on the selected Card.
	 If set to true(1), the AP will turn on the OBSS Coexistence for that card.
	 If set  to false(2) the AP will  disable the OBSS Coexistence for the card."
    ::= { cmdot11BaseEntry 14 }

cmdot11WifiAcsdScanTimer OBJECT-TYPE
    SYNTAX      Unsigned32  (0..268435454)
    UNITS       "seconds"
    MAX-ACCESS  read-write
    STATUS      current
    DESCRIPTION
        "Controls and reflects the ACS Scan Timer for this interface."
    ::= { cmdot11BaseEntry 15 }

cmdot11WifiWMFEnable OBJECT-TYPE
    SYNTAX      TruthValue
    MAX-ACCESS  read-write
    STATUS      current
    DESCRIPTION
        "Controls and reflects the state of Wifi Radio's Wireless Multicast Forwarding (WMF).
	   Set to true(1) to enable the WMF feature.
	   Set to false(2) to disable the WMF feature."
    ::= { cmdot11BaseEntry 16 }

cmdot11WifiBSEnable OBJECT-TYPE
    SYNTAX      TruthValue
    MAX-ACCESS  read-write
    STATUS      current
    DESCRIPTION
        "Controls and reflects the state of Wifi Radio's Band steering capability.
	   Set to true(1) to enable the Band steering feature.
	   Set to false(2) to disable the Band steering feature."
    ::= { cmdot11BaseEntry 17 }

cmdot11WifiATFEnable OBJECT-TYPE
    SYNTAX      TruthValue
    MAX-ACCESS  read-write
    STATUS      current
    DESCRIPTION
        "Controls and reflects the state of Wifi Radio's Air Time Fairness capability.
	   Set to true(1) to enable the ATF feature.
	   Set to false(2) to disable the ATF feature."
    ::= { cmdot11BaseEntry 18 }

cmdot11WifiTrafficSchedulerEnable OBJECT-TYPE
    SYNTAX      TruthValue
    MAX-ACCESS  read-write
    STATUS      current
    DESCRIPTION
        "Controls and reflects the state of Wifi Radio's Traffic Scheduling capability.
	   Set to true(1)to enable the Traffic Scheduler feature.
	   Set to false(2) to disable the Traffic Scheduler feature."
    ::= { cmdot11BaseEntry 19 }

cmdot11WifiEbosEnable OBJECT-TYPE
    SYNTAX      TruthValue
    MAX-ACCESS  read-write
    STATUS      current
    DESCRIPTION
        "Controls and reflects the state of Wifi Radio's Exhausted Buffer Order Scheduling capability.
	   Set to true(1) to enable the EBOS feature.
	   Set to false(2) to disable the EBOS feature."
    ::= { cmdot11BaseEntry 20 }

cmdot11gTable  OBJECT-TYPE
    SYNTAX      SEQUENCE OF Cmdot11gEntry
    MAX-ACCESS  not-accessible
    STATUS      current
    DESCRIPTION
        "A table of settings used to configure all wi-fi interfaces which are
         capable of supporting the ieee 802.11g standard."
    ::= { cmdot11MgmtInterfaceTables 2 }

cmdot11gEntry OBJECT-TYPE
    SYNTAX      Cmdot11gEntry
    MAX-ACCESS  not-accessible
    STATUS      current
    DESCRIPTION
        "An entry describing the configuration of 802.11g specific parameters
         for a primary wifi interface.

         An entry exists in this table for each entry in the ifTable with an
         ifType value of ieee80211(71), which is designated as a primary
         wi-fi interface in the ifTable, and which is capable of supporting the
         IEEE 802.11g standard.

         Note that non-primary interfaces such as Guest network interfaces are not
         represented in this table."
    INDEX   { ifIndex }
    ::= { cmdot11gTable  1 }

Cmdot11gEntry ::=
    SEQUENCE    {
        cmdot11Wifi54gNetMode          INTEGER,
        cmdot11Wifi54gProtectionEnable TruthValue,
        cmdot11Wifi54gBasicRateSet     INTEGER
    }

cmdot11Wifi54gNetMode OBJECT-TYPE
    SYNTAX      INTEGER {
		mode54g11bOnly(0),
		mode54gAuto(1),
		mode54gOnly(2),
		mode54gPerformance(4),
		mode54gLRS(5)
    }
    MAX-ACCESS  read-write
    STATUS      current
    DESCRIPTION
        "Controls and reflects the behavior of the interface with regards to
         which flavor of 802.11g is used.
         If set to mode54g11bOnly(0), only 802.11b clients will be accepted.
         If set to mode54gAuto(1) the interface will attempt to operate at 54g
         rates unless an 802.11b client is detected.

         If set to mode54gOnly(2), only 802.11g clients will be accepted.
         If set to mode54gPerformance(4), the highest throughout will be provided
         and only 54g clients will be accepted, however nearby 802.11b networks
         may suffer degraded performance.
         If set to mode54gLRS(5), the interface will interoperate with the
         widest variety of 54g and 802.11b clients."

    DEFVAL { mode54gAuto }
    ::= { cmdot11gEntry 1 }

cmdot11Wifi54gProtectionEnable OBJECT-TYPE
    SYNTAX      TruthValue
    MAX-ACCESS  read-write
    STATUS      current
    DESCRIPTION
        "Controls and reflects the state of 54g protection.  If set to true(1),
         the AP will use RTS/CTS to improve 802.11g performance in mixed
         802.11g/802.11b networks.  Set to false(2) to maximize 802.11g
         throughput under most conditions."
    DEFVAL { false }
    ::= { cmdot11gEntry 2 }

cmdot11Wifi54gBasicRateSet OBJECT-TYPE
    SYNTAX      INTEGER {
		default(1),
		all(2)
    }
    MAX-ACCESS  read-write
    STATUS      current
    DESCRIPTION
        "Determines which rates are advertised as BASIC rates in the beacon.
    	 If set to default, the driver defaults for the selected 54gMode will
    	 be used.  If set to all, all available rates will be advertised as
    	 BASIC rates regardless of the 54gMode setting."
    DEFVAL { default }
    ::= { cmdot11gEntry 3 }


cmdot11nTable  OBJECT-TYPE
    SYNTAX      SEQUENCE OF Cmdot11nEntry
    MAX-ACCESS  not-accessible
    STATUS      current
    DESCRIPTION
        "A table of settings used to configure all wi-fi interfaces which are
         capable of supporting the ieee 802.11n standard."
    ::= { cmdot11MgmtInterfaceTables 3 }

cmdot11nEntry OBJECT-TYPE
    SYNTAX      Cmdot11nEntry
    MAX-ACCESS  not-accessible
    STATUS      current
    DESCRIPTION
        "An entry describing the configuration of 802.11n specific parameters
         for a primary wifi interface.

         An entry exists in this table for each entry in the ifTable with an
         ifType value of ieee80211(71), which is designated as a base
         wi-fi interface in the ifTable, and which is capable of supporting the
         IEEE 802.11n standard.

         Note that non-primary interfaces such as Guest network interfaces are not
         represented in this table."
    INDEX   { ifIndex }
    ::= { cmdot11nTable 1 }

Cmdot11nEntry ::=
    SEQUENCE    {
        cmdot11WifiNMode           INTEGER,
        cmdot11WifiNPhyRate        INTEGER,
        cmdot11WifiNBand           INTEGER,
        cmdot11WifiNBandWidth      INTEGER,
        cmdot11WifiNSideBand       INTEGER,
        cmdot11WifiNProtection     INTEGER
    }

cmdot11WifiNMode OBJECT-TYPE
    SYNTAX      INTEGER {
		auto(1),
		off(2),
		nOnly(3)
    }
    MAX-ACCESS  read-write
    STATUS      current
    DESCRIPTION
            "Used to enable/disable 802.11n operation.
            'Auto' is used to enable 802.11n operation; the Access Point will detect which
             stations are out there and operate in the proper mode.
            'Off' is used to disable 802.11n operation; the Access Point will operate in the
             mode specified by cmdot1154gNetMode. The nOnly setting will configure the
             card to operate only in N mode - 'b' and 'g' modes will be inhibited.

             Note: This MIB object is only valid for products supporting 802.11n,
             and also affects other MIB selections."
    ::= { cmdot11nEntry 1 }

cmdot11WifiNPhyRate OBJECT-TYPE
    SYNTAX      INTEGER {
        auto(0),
        legacy(1),
        mcs0(2),
        mcs1(3),
        mcs2(4),
        mcs3(5),
        mcs4(6),
        mcs5(7),
        mcs6(8),
        mcs7(9),
        mcs8(10),
        mcs9(11),
        mcs10(12),
        mcs11(13),
        mcs12(14),
        mcs13(15),
        mcs14(16),
        mcs15(17)
    }
    MAX-ACCESS  read-write
    STATUS      current
    DESCRIPTION
            "Used to specify the 802.11n PHY transmission rate.
            'Auto' is used to allow the Access Point to dynamically adapt
            to the environment and transmit using the fastest data rate
            for the given environmental conditions.
            'Legacy' is used to restrict the transmission to 802.11b/g rates.
            'mcs0' through 'mcs15' are used to force the 802.11N PHY transmission
            rate for the Access Point to a particular speed. The MCS-to-speed mapping
            is provided by the 802.11n spec and depends on whether a 20 MHz
            channel or a 40 MHz channel is being used.
            Note: This MIB object is only valid for products supporting 802.11n."
    DEFVAL { auto }
    ::= { cmdot11nEntry  2 }

cmdot11WifiNBand OBJECT-TYPE
    SYNTAX      INTEGER {
        band-2-4G(1),
        band-5G(2)
    }
    MAX-ACCESS  read-write
    STATUS      current
    DESCRIPTION
            "Selects the wireless frequency band (2.4 GHz or 5 GHz) the Access Point will operate in.
            Note: This MIB object is only valid for products supporting 802.11n."
    ::= { cmdot11nEntry  3 }

cmdot11WifiNBandWidth OBJECT-TYPE
    SYNTAX      INTEGER {
	none(0),
        width-20MHz(1),
        width-40MHz(2)
    }
    MAX-ACCESS  read-write
    STATUS      current
    DESCRIPTION
            "Specifies the channel width (20 MHz or 20/40 MHz) to be used by the Access Point.
            When 20/40MHz is selected 802.11n clients experience improved throughput
            using 40 MHz, while legacy clients(either 802.11a or 802.11b/g) can
            still be serviced without interruption using 20MHz.
            If neither 20 MHz nor 40 MHz is used, the mib returns none(0).
            Note: This MIB object is only valid for products supporting 802.11n, and
            also affects other MIB selections such as cmdot11NSideBand."
    ::= { cmdot11nEntry  4 }

cmdot11WifiNSideBand OBJECT-TYPE
    SYNTAX      INTEGER {
		none(0),
		upper(1),
		lower(2)
    }
    MAX-ACCESS  read-write
    STATUS      current
    DESCRIPTION
            "When bonded channels (40 MHz) are used this object specifies if the
             control (primary) channel is in the lower or upper 20 MHz band of the
             bonded 40 MHz channel. Returns none(0) when cmdot11WifiNBandWidth != 40MHz.
             Note: This MIB object is only valid for products supporting 802.11n and
             only applies when cmdot11NBandWidth is set to 20/40MHz."
    ::= { cmdot11nEntry  5 }

cmdot11WifiNProtection OBJECT-TYPE
    SYNTAX      INTEGER {
		auto(1),
		off(2)
    }
    MAX-ACCESS  read-write
    STATUS      current
    DESCRIPTION
            "Determines if protection will be turned on or off for 802.11n mode.
             When set to auto, the Access Point will enable protection to allow
             802.11n clients to co-exist with 802.11a/b/g clients.
             Note: This MIB object is only valid for products supporting 802.11n."
    ::= { cmdot11nEntry  6 }
cmdot11ApsScanResultsTable  OBJECT-TYPE
    SYNTAX      SEQUENCE OF Cmdot11ApsScanResultsEntry
    MAX-ACCESS  not-accessible
    STATUS      current
    DESCRIPTION
        "A table list of neighboring APs found after cmdot11WifiApsScan
        in cmdot11BaseTable is set to true. The table can list up to 32 APs."
    ::= { cmdot11MgmtInterfaceTables 4 }
cmdot11ApsScanResultsEntry OBJECT-TYPE
    SYNTAX      Cmdot11ApsScanResultsEntry
    MAX-ACCESS  not-accessible
    STATUS      current
    DESCRIPTION
        "An entry describing neighboring AP information. First element cmdot11ValidEntry
        determines if the current entry is valid or not. The information includes
        SSID, RSSI, Channel, Mac Address etc."
    INDEX   { ifIndex }
    ::= { cmdot11ApsScanResultsTable 1 }

Cmdot11ApsScanResultsEntry ::=
    SEQUENCE    {
        cmdot11ValidEntry      INTEGER,
        cmdot11NetworkName     OCTET STRING,
        cmdot11SecurityMode    OCTET STRING,
        cmdot11PhyMode         OCTET STRING,
        cmdot11Rssi            INTEGER,
        cmdot11Channel         INTEGER,
        cmdot11MacAddress      PhysAddress
    }

cmdot11ValidEntry OBJECT-TYPE
    SYNTAX      INTEGER {
                invalid(0),
                valid(1)
    }
    MAX-ACCESS  read-only
    STATUS      current
    DESCRIPTION
        "Determines if the current entry is valid or not."
    ::= { cmdot11ApsScanResultsEntry 1 }

cmdot11NetworkName OBJECT-TYPE
    SYNTAX      OCTET STRING
    MAX-ACCESS  read-only
    STATUS      current
    DESCRIPTION
        "Neighboring AP name or SSID."
    ::= { cmdot11ApsScanResultsEntry 2 }
cmdot11SecurityMode OBJECT-TYPE
    SYNTAX      OCTET STRING
    MAX-ACCESS  read-only
    STATUS      current
    DESCRIPTION
        "Neighboring AP security mode."
    ::= { cmdot11ApsScanResultsEntry 3 }

cmdot11PhyMode OBJECT-TYPE
    SYNTAX      OCTET STRING
    MAX-ACCESS  read-only
    STATUS      current
    DESCRIPTION
        "Neighboring AP PHY mode."
    ::= { cmdot11ApsScanResultsEntry 4 }

cmdot11Rssi OBJECT-TYPE
    SYNTAX      INTEGER
    MAX-ACCESS  read-only
    STATUS      current
    DESCRIPTION
        "Neighboring AP receive signal strength."
    ::= { cmdot11ApsScanResultsEntry 5 }
cmdot11Channel OBJECT-TYPE
    SYNTAX      INTEGER
    MAX-ACCESS  read-only
    STATUS      current
    DESCRIPTION
        "Neighboring AP operating channel."
    ::= { cmdot11ApsScanResultsEntry 6 }

cmdot11MacAddress OBJECT-TYPE
    SYNTAX      PhysAddress
    MAX-ACCESS  read-only
    STATUS      current
    DESCRIPTION
        "Neighboring AP MAC address."
    ::= { cmdot11ApsScanResultsEntry 7 }


cmdot1180211acInterfaceTable  OBJECT-TYPE
    SYNTAX      SEQUENCE OF Cmdot1180211acInterfaceEntry
    MAX-ACCESS  not-accessible
    STATUS      current
    DESCRIPTION
        "A table of settings used to configure all wi-fi interfaces which are
         capable of supporting the ieee 802.11ac standard."
    ::= { cmdot11MgmtInterfaceTables 5 }

cmdot1180211acInterfaceEntry OBJECT-TYPE
    SYNTAX      Cmdot1180211acInterfaceEntry
    MAX-ACCESS  not-accessible
    STATUS      current
    DESCRIPTION
        "An entry describing the configuration of 802.11ac specific parameters
         for a primary wifi interface.

         An entry exists in this table for each entry in the ifTable with an
         ifType value of ieee80211(71), which is designated as a primary
         wi-fi interface in the ifTable, and which is capable of supporting the
         IEEE 802.11ac standard.

         Note that non-primary interfaces such as Guest network interfaces are not
         represented in this table."
    INDEX   { ifIndex }
    ::= { cmdot1180211acInterfaceTable 1 }

Cmdot1180211acInterfaceEntry ::=
    SEQUENCE    {
        cmdot11ACBandWidth      INTEGER,
        cmdot11ACChannelSpec    OCTET STRING,
        cmdot11ACTxbfBFRCap     TruthValue,
        cmdot11ACTxbfBFECap	TruthValue
    }

cmdot11ACBandWidth OBJECT-TYPE
    SYNTAX      INTEGER {
		width20MHz(1),
		width40MHz(2),
		width80MHz(3)
    }
    MAX-ACCESS  read-write
    STATUS      current
    DESCRIPTION
        "Determines which Bandwidth that we will be operating in:
         20MHz, 40MHz or 80MHz.  Note: This is for N or AC cards only."
    ::= { cmdot1180211acInterfaceEntry 1 }

cmdot11ACChannelSpec OBJECT-TYPE
    SYNTAX      OCTET STRING (SIZE(1..20))
    MAX-ACCESS  read-write
    STATUS      current
    DESCRIPTION
        "Controls and reflects the current channel specification for this interface.
         If set to (0), the AP will be put in auto-channel mode where
	     it automatically scans for the least-crowded channel.
         For 20MHz bandwidth, channel specifications are control channel.
             For example 1, 36 etc.
         For 40MHz bandwidth, channel specifications are a combination of control channel
             and sideband ('u' is for upper sideband and 'l' is for lower sideband).
             For example 5u, 1l, 40u, 36l etc.
         For 80MHz bandwidth, channel specifications are 36/80, 52/80, 100/80 etc.
         Channel specification selection is also subject to restrictions based on the
	     selected country code."
    ::= { cmdot1180211acInterfaceEntry 2 }

cmdot11ACTxbfBFRCap OBJECT-TYPE
    SYNTAX      TruthValue
    MAX-ACCESS  read-write
    STATUS      current
    DESCRIPTION
        "Controls and reflects the BFR Capability on the selected Card.
	   Set to true(1) to enable the BFR Capability for that card.
	   Set to false(2) to disable the BFR Capability for that card."
    ::= { cmdot1180211acInterfaceEntry 3 }

cmdot11ACTxbfBFECap OBJECT-TYPE
    SYNTAX      TruthValue
    MAX-ACCESS  read-write
    STATUS      current
    DESCRIPTION
        "Controls and reflects the BFE Capability on the selected Card.
  	   Set to true(1) to enable the BFE Capability for that card.
           Set to false(2) to disable the BFE Capability for that card."
    ::= { cmdot1180211acInterfaceEntry 4 }

--
-- cmdot11MgmtMbss contains objects used for managing configuration of all
-- basic service sets in an access point which may have multiple BSS's.
-- Note that if a system is not MBSS capable, the same objects are still used
-- but the tables will have a single entry rather than several.
--

cmdot11MgmtMbss OBJECT IDENTIFIER ::= { cmdot11plusMgmtv2 4 }

--
-- cmdot11MbssBase contains objects used to configure basic operation
-- of each service set.
--

cmdot11MbssBase OBJECT IDENTIFIER ::= { cmdot11MgmtMbss 1 }

cmdot11BssTable   OBJECT-TYPE
    SYNTAX      SEQUENCE OF Cmdot11BssEntry
    MAX-ACCESS  not-accessible
    STATUS      current
    DESCRIPTION
        "A table of entries in an MBSS system.
        "
    ::= { cmdot11MbssBase 14 }

cmdot11BssEntry OBJECT-TYPE
    SYNTAX      Cmdot11BssEntry
    MAX-ACCESS  not-accessible
    STATUS      current
    DESCRIPTION
        "An entry describing the characteristics of an individual BSS.  An
         entry exists in this table for each entry of type ieee80211 (71) in
         the ifTable.
        "
    INDEX   { ifIndex }
    ::= { cmdot11BssTable 1 }

Cmdot11BssEntry ::=
    SEQUENCE    {
                cmdot11BssId                      PhysAddress,
                cmdot11BssEnable                  TruthValue,
                cmdot11BssSsid                    OCTET STRING,
                cmdot11BssNetworkBridge           INTEGER,
                cmdot11BssSecurityMode            INTEGER,
                cmdot11BssClosedNetwork           TruthValue,
                cmdot11BssAccessMode              INTEGER,
		cmdot11BssMaxAssociationsLimit    Unsigned32,
                cmdot11BssOpmodeCapRequired       INTEGER
    }

cmdot11BssId OBJECT-TYPE
    SYNTAX      PhysAddress
    MAX-ACCESS  read-only
    STATUS      current
    DESCRIPTION
        "The physical address associated with this service set.
        "
    ::= { cmdot11BssEntry 1 }

cmdot11BssEnable OBJECT-TYPE
    SYNTAX      TruthValue
    MAX-ACCESS  read-write
    STATUS      current
    DESCRIPTION
        "Enables or disables this service set.
        "
    ::= { cmdot11BssEntry 2 }

cmdot11BssSsid OBJECT-TYPE
    SYNTAX      OCTET STRING (SIZE(0..32))
    MAX-ACCESS  read-write
    STATUS      current
    DESCRIPTION
        "Controls and reflects the service set identifier for this BSS.
        "
    ::= { cmdot11BssEntry 3 }

cmdot11BssNetworkBridge OBJECT-TYPE
    SYNTAX      INTEGER {
                lan(1),
                guest(2)
    }
    MAX-ACCESS  read-write
    STATUS      obsolete
    DESCRIPTION
        "If set to lan(1), this service set will be authorized as a member of
         the local area network.  If set to guest(2), this service set will
         have access to the wide area internet, but will have restricted access
         to the local area network.
         "
    ::= { cmdot11BssEntry 4 }

cmdot11BssSecurityMode OBJECT-TYPE
    SYNTAX      INTEGER {
                disabled(0),
                wep(1),
                wpaPsk(2),
                wpa2Psk(3),
                wpaEnterprise(4),
                wpa2Enterprise(5),
                radiusWep(6),
                wpaPsk-wpa2Psk(7),
                wpaEnterprise-wpa2Enterprise(8)
    }
    MAX-ACCESS  read-write
    STATUS      current
    DESCRIPTION
        "Security mode may be chosen from Disable, WEP, WPA-PSK, WPA2-PSK,
         WPA-Enterprise, WPA2-Enterprise, RADIUS-WEP, WPA-PSK_WPA2-PSK or
         WPA-Enterprise_WPA2-Enterprise.  All devices on the network must use
         the same security mode in order to communicate.

         If set to disabled(0):
            Open system. No authentication or encryption.

         If set to wep(1) then the following parameters must be set:
            Default Transmit Key (cmdot11BssWepDefaultKey):
                Choose which Key to use.
            WEP Key Bit (cmdot11BssWepEncryptionMode):
                May select from 64-Bit or 128-Bit encryption.
            Passphrase (cmdot11BssWepPassPhrase):
                Enter a passphrase consisting of any keyboard character
                to be used to generate a hex WEP key.
            Key 1-4 (cmdot11BssWep64BitKeyTable or cmdot11BssWep128BitKeyTable):
                Enter a WEP key manually. Must use only hex character (0-9 and A-F).
                64-bit WEP requires 10 hex characters, 128-Bit WEP requires the use of
                26 hex characters.

         If set to wpaPsk(2) then the following parameters must be set:
            WPA Algorithm (cmdot11BssWpaAlgorithm):
                TKIP or AES.
            WPA Pre-Shared Key (cmdot11BssWpaPreSharedKey):
                Choose a unique key to authenticate with other devices on the network.
                The Pre-Shared Key must be between 8 and 63 characters in length.
            Group Key Renewal (cmdot11BssWpaGroupRekeyInterval):
                This settings determines how often the group key changes.

         If set to wpa2Psk(3) then the following parameters must be set:
            WPA2 Algorithm (cmdot11BssWpaAlgorithm):
                AES or TKIP+AES.
            WPA2 Pre-Shared Key (cmdot11BssWpaPreSharedKey):
                Choose a unique key to authenticate with other devices on the network.
                The Pre-Shared Key must be between 8 and 63 characters in length.
            Group Key Renewal (cmdot11BssWpaGroupRekeyInterval):
                This settings determines how often the group key changes.

         If set to wpaEnterprise(4) then the following parameters must be set:
            WPA Algorithm (cmdot11BssWpaAlgorithm):
                TKIP or AES.
            RADIUS Server Address (cmdot11BssRadiusAddress):
                The IP address of the RADIUS server.
            RADIUS Server Port (cmdot11BssRadiusPort):
                The port the RADIUS server uses.
            RADIUS Shared Secret (cmdot11BssRadiusKey):
                The shared secret set on the RADIUS server.
            Key Renewal Timeout (cmdot11BssRadiusReAuthInterval):
                Determines how often the keys should be renewed.

         If set to wpa2Enterprise(5) then the following parameters must be set:
            WPA2 Algorithm (cmdot11BssWpaAlgorithm):
                AES or TKIP+AES.
            RADIUS Server Address (cmdot11BssRadiusAddress):
                The IP address of the RADIUS server.
            RADIUS Server Port (cmdot11BssRadiusPort):
                The port the RADIUS server uses.
            RADIUS Shared Secret (cmdot11BssRadiusKey):
                The shared secret set on the RADIUS server.
            Key Renewal Timeout (cmdot11BssRadiusReAuthInterval):
                Determines how often the keys should be renewed.

         If set to radiusWep(6) then the following parameters must be set:
            RADIUS Server Address (cmdot11BssRadiusAddressType / cmdot11BssRadiusAddress):
                The IP address of the RADIUS server.
            RADIUS Server Port (cmdot11BssRadiusPort):
                The port the RADIUS server uses.
            RADIUS Shared Secret (cmdot11BssRadiusKey):
                The shared secret set on the RADIUS server.
            Default Transmit Key (cmdot11BssWepDefaultKey):
                Choose which Key to use.
            WEP Key Bit (cmdot11BssWepEncryptionMode):
                May select from 64-Bit or 128-Bit encryption.
            Passphrase (cmdot11BssWepPassPhrase):
                Enter a passphrase consisting of any keyboard character
                to be used to generate a hex WEP key.
            Key 1-4 (cmdot11BssWep64BitKeyTable or cmdot11BssWep128BitKeyTable):
                Enter a WEP key manually. Must use only hex character (0-9 and A-F).
                64-bit WEP requires 10 hex characters, 128-Bit WEP requires the use of
                26 hex characters.

         If set to wpaPsk-wpa2Psk(7) then the following parameters must be set:
            WPA or WPA2 Algorithm (cmdot11BssWpaAlgorithm):
                AES or TKIP+AES.
            WPA or WPA2 Pre-Shared Key (cmdot11BssWpaPreSharedKey):
                Choose a unique key to authenticate with other devices on the network.
                The Pre-Shared Key must be between 8 and 63 characters in length.
            Group Key Renewal (cmdot11BssWpaGroupRekeyInterval):
                This settings determines how often the group key changes.

         If set to wpaEnterprise-wpa2Enterprise(8) then the following parameters must be set:
            WPA2 Algorithm (cmdot11BssWpaAlgorithm):
                AES or TKIP+AES.
            RADIUS Server Address (cmdot11BssRadiusAddress):
                The IP address of the RADIUS server.
            RADIUS Server Port (cmdot11BssRadiusPort):
                The port the RADIUS server uses.
            RADIUS Shared Secret (cmdot11BssRadiusKey):
                The shared secret set on the RADIUS server.
            Key Renewal Timeout (cmdot11BssRadiusReAuthInterval):
                Determines how often the keys should be renewed.

                "
    ::= { cmdot11BssEntry 5 }

cmdot11BssClosedNetwork OBJECT-TYPE
    SYNTAX      TruthValue
    MAX-ACCESS  read-write
    STATUS      current
    DESCRIPTION
        "Controls whether the device will operate in closed network mode.  If
         set to true(1), then the network mode is closed and the SSID will not
         be broadcast in beacon packets.  If set to false(2), then the network
         mode is open and the SSID will be broadcast in beacon packets.
        "
    ::= { cmdot11BssEntry 6 }

cmdot11BssAccessMode OBJECT-TYPE
    SYNTAX      INTEGER {
                allowAny(1),
                allowList(2),
                denyList(3)
    }
    MAX-ACCESS  read-write
    STATUS      current
    DESCRIPTION
        "Controls what stations will be given access to the device.  If set to
         allowAny(1), then any station will be allowed to connect.  If set
         to restrictToList(2), then only stations whose MAC address appears in
         the cmdot11BssAccessTable will be allowed to connect.  If set to
         denyList(3), any station will be allowed to connect except those in
         the cmdot11BssAccessTable.
        "
    ::= { cmdot11BssEntry 7 }

cmdot11BssMaxAssociationsLimit OBJECT-TYPE
    SYNTAX      Unsigned32  (1..128)
    MAX-ACCESS  read-write
    STATUS      current
    DESCRIPTION
        "Configure the maximum number of stations that can associate with
         the device."
    ::= { cmdot11BssEntry 8 }

cmdot11BssOpmodeCapRequired OBJECT-TYPE
SYNTAX      INTEGER  {
    none(0),
    erp(1),
    ht(2),
    vht(3)
}
    MAX-ACCESS  read-write
    STATUS      current
    DESCRIPTION
        "Configure operational capability requirement for a STA to associate to the BSS."
    ::= { cmdot11BssEntry 9 }

--
-- cmdot11MbssSecurity contains objects used to configure security options
-- of each service set.
--

cmdot11MbssSecurity OBJECT IDENTIFIER ::= { cmdot11MgmtMbss 2 }

-- Objects used to control WEP based security modes

cmdot11BssWepTable   OBJECT-TYPE
    SYNTAX      SEQUENCE OF Cmdot11BssWepEntry
    MAX-ACCESS  not-accessible
    STATUS      current
    DESCRIPTION
        "A table used to configure settings related to the WEP security modes.
        "
    ::= { cmdot11MbssSecurity 1 }

cmdot11BssWepEntry OBJECT-TYPE
    SYNTAX      Cmdot11BssWepEntry
    MAX-ACCESS  not-accessible
    STATUS      current
    DESCRIPTION
        "An entry defining the WEP characteristics of an individual service set.
         A row exists in this table for each row in the cmdot11BssTable for which
         cmdot11BssSecurityMode is set to wep(1) or radiusWep(6).
        "
    INDEX   { ifIndex }
    ::= { cmdot11BssWepTable 1 }

Cmdot11BssWepEntry ::=
    SEQUENCE    {
                cmdot11BssWepDefaultKey           		Unsigned32,
                cmdot11BssWepEncryptionMode       		INTEGER,
                cmdot11BssWepPassPhrase           		DisplayString,
                cmdot11BssWepSharedKeyAuthentication            INTEGER
    }

cmdot11BssWepDefaultKey OBJECT-TYPE
    SYNTAX      Unsigned32
    MAX-ACCESS  read-write
    STATUS      current
    DESCRIPTION
        "Controls and reflects the default key which will be used when 64 or
         128 bit encryption is enabled.  Indicates the entry from the
         cmdot11BssWep64BitKeyTable if cmdot11EncryptionMode is set to wep64(1), or
         the entry from the cmdot11BssWep128BitKeyTable if cmdot11BssSecurityMode
         is set to wep128(2).

         This object may only be set to indicate an active row in the
         cmdot11BssWep64BitKeyTable or cmdot11BssWep128BitKeyTable.  If the value
         corresponds to a row which does not exist or a row which is not
         active, the set will be rejected with an inconsistentValue error.
        "
    ::= { cmdot11BssWepEntry 1 }

cmdot11BssWepEncryptionMode OBJECT-TYPE
    SYNTAX      INTEGER {
                wep64(1),
                wep128(2)
    }
    MAX-ACCESS  read-write
    STATUS      current
    DESCRIPTION
        "Selects the WEP encryption method used by this service set.
         If set to wep64(1), then 64 bit WEP encryption will be
         used with the keys from the cmdot11BssWep64BitKeyTable.  If set to
         wep128(2), then 128 bit WEP encryption will be used with keys from
         the cmdot11BssWep128BitKeyTable.
        "
    ::= { cmdot11BssWepEntry 2 }

cmdot11BssWepPassPhrase OBJECT-TYPE
    SYNTAX      DisplayString (SIZE(0..32))
    MAX-ACCESS  read-write
    STATUS      current
    DESCRIPTION
        "The passphrase used for WEP security.
        "
    ::= { cmdot11BssWepEntry 3 }

cmdot11BssWepSharedKeyAuthentication OBJECT-TYPE
    SYNTAX      INTEGER
    		    {
    		     optional(1),
    		     required(2)
    		    }
    MAX-ACCESS  read-write
    STATUS      current
    DESCRIPTION
        "This object controls the use of Shared Key authentication in WEP protocol. If this object
         is set to optional(1), Shared Key authentication is optional. If set to required(2),
         Shared Key authentication is required for WEP.
        "
    ::= { cmdot11BssWepEntry 4 }

cmdot11BssWep64BitKeyTable OBJECT-TYPE
    SYNTAX      SEQUENCE OF Cmdot11BssWep64BitKeyEntry
    MAX-ACCESS  not-accessible
    STATUS      current
    DESCRIPTION
        "A table of 40 bit key values used when operating in WEP 64 mode."
    ::= { cmdot11MbssSecurity 2 }

cmdot11BssWep64BitKeyEntry OBJECT-TYPE
    SYNTAX      Cmdot11BssWep64BitKeyEntry
    MAX-ACCESS  not-accessible
    STATUS      current
    DESCRIPTION
        "A key to be used by the row in the cmdot11BssTable identified by the
         value of ifIndex in the row index. "
    INDEX   { ifIndex, cmdot11BssWep64BitKeyIndex }
    ::= { cmdot11BssWep64BitKeyTable 1 }

Cmdot11BssWep64BitKeyEntry ::=
    SEQUENCE    {
                cmdot11BssWep64BitKeyIndex           Integer32,
                cmdot11BssWep64BitKeyValue           OCTET STRING,
                cmdot11BssWep64BitKeyStatus          RowStatus
    }

cmdot11BssWep64BitKeyIndex OBJECT-TYPE
    SYNTAX      Integer32 (1..4)
    MAX-ACCESS  not-accessible
    STATUS      current
    DESCRIPTION
        "Identifies an instance of a key among those used by the service set
         identified by the value of ifIndex in the row index."
    ::= { cmdot11BssWep64BitKeyEntry 1 }

cmdot11BssWep64BitKeyValue OBJECT-TYPE
    SYNTAX      OCTET STRING (SIZE(5))
    MAX-ACCESS  read-create
    STATUS      current
    DESCRIPTION
        "A 40 bit key to be used when the corresponding instance of
         cmdot11BssSecurityMode is set to wep(1) and the corresponding instance
         of cmdot11BssWepEncryptionMode is set to wep64(1)."
    ::= { cmdot11BssWep64BitKeyEntry 2 }

cmdot11BssWep64BitKeyStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         cmdot11BssAccessStatus column is 'notReady'.

         In particular, a newly created row cannot be made active until the
         corresponding instance of cmdot11BssWep64BitKeyValue has been set.

         Only rows with a status of active(1) will be applied.

         This object may not be set to a value of notInService(2) or destroy(6)
         if the corresponding instance of cmdot11BssWepDefaultKey identifies
         this row as they current key in use.  Such an attempt will be rejected
         with an inconsistentValue error."
    ::= { cmdot11BssWep64BitKeyEntry 3 }


cmdot11BssWep128BitKeyTable OBJECT-TYPE
    SYNTAX      SEQUENCE OF Cmdot11BssWep128BitKeyEntry
    MAX-ACCESS  not-accessible
    STATUS      current
    DESCRIPTION
        "A table of 104 bit key values used when operating in WEP 128 mode."
    ::= { cmdot11MbssSecurity 3 }

cmdot11BssWep128BitKeyEntry OBJECT-TYPE
    SYNTAX      Cmdot11BssWep128BitKeyEntry
    MAX-ACCESS  not-accessible
    STATUS      current
    DESCRIPTION
        "A key to be used by the row in the cmdot11BssTable identified by the
         value of ifIndex in the row index."
    INDEX   { ifIndex, cmdot11BssWep128BitKeyIndex }
    ::= { cmdot11BssWep128BitKeyTable 1 }

Cmdot11BssWep128BitKeyEntry ::=
    SEQUENCE    {
                cmdot11BssWep128BitKeyIndex           Integer32,
                cmdot11BssWep128BitKeyValue           OCTET STRING,
                cmdot11BssWep128BitKeyStatus          RowStatus
    }

cmdot11BssWep128BitKeyIndex OBJECT-TYPE
    SYNTAX      Integer32 (1..4)
    MAX-ACCESS  not-accessible
    STATUS      current
    DESCRIPTION
        "Identifies an instance of a key among those used by the service set
         identified by the value of ifIndex in the row index."
    ::= { cmdot11BssWep128BitKeyEntry 1 }

cmdot11BssWep128BitKeyValue OBJECT-TYPE
    SYNTAX      OCTET STRING (SIZE(13))
    MAX-ACCESS  read-create
    STATUS      current
    DESCRIPTION
        "A 104 bit key to be used when the corresponding instance of
         cmdot11BssSecurityMode is set to wep(1) and the corresponding instance
         of cmdot11BssWepEncryptionMode is set to wep128(128)."
    ::= { cmdot11BssWep128BitKeyEntry 2 }

cmdot11BssWep128BitKeyStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         cmdot11BssAccessStatus column is 'notReady'.

         In particular, a newly created row cannot be made active until the
         corresponding instance of cmdot11BssWep128BitKeyValue has been set.

         Only rows with a status of active(1) will be applied.

         This object may not be set to a value of notInService(2) or destroy(6)
         if the corresponding instance of cmdot11BssWepDefaultKey identifies
         this row as the current key in use.  Such an attempt will be rejected
         with an inconsistentValue error.
        "
    ::= { cmdot11BssWep128BitKeyEntry 3 }

-- Objects used to control WPA based security modes

cmdot11BssWpaTable   OBJECT-TYPE
    SYNTAX      SEQUENCE OF Cmdot11BssWpaEntry
    MAX-ACCESS  not-accessible
    STATUS      current
    DESCRIPTION
        "A table used to configure settings related to the WPA security modes.
        "
    ::= { cmdot11MbssSecurity 4 }

cmdot11BssWpaEntry OBJECT-TYPE
    SYNTAX      Cmdot11BssWpaEntry
    MAX-ACCESS  not-accessible
    STATUS      current
    DESCRIPTION
        "An entry defining the WPA characteristics of an individual service set.
         A row exists in this table for each row in the cmdot11BssTable for which
         cmdot11BssSecurityMode is set to wpaPsk(2), wpa2Psk(3), wpaEnterprise(4),
         or wpa2Enterprise(5).
        "
    INDEX   { ifIndex }
    ::= { cmdot11BssWpaTable 1 }

Cmdot11BssWpaEntry ::=
    SEQUENCE    {
                cmdot11BssWpaAlgorithm            INTEGER,
                cmdot11BssWpaPreSharedKey         OCTET STRING,
                cmdot11BssWpaGroupRekeyInterval   Unsigned32
    }

cmdot11BssWpaAlgorithm OBJECT-TYPE
    SYNTAX      INTEGER {
                tkip(1),
                aes(2),
                tkipPlusAes(3)
    }
    MAX-ACCESS  read-write
    STATUS      current
    DESCRIPTION
        "Controls and reflects the WPA encryption mode used by the service set.
         The WPA algorithm for WPA-PSK and WPA-Enterprise security mode is either
         tkip(1) or aes(2).

         The WPA algorithm for WPA2-PSK and WPA2-Enterprise security mode is either
         aes(2) or tkipPlusAes(3).
        "
    ::= { cmdot11BssWpaEntry 1 }

cmdot11BssWpaPreSharedKey OBJECT-TYPE
    SYNTAX      OCTET STRING (SIZE (8..64))
    MAX-ACCESS  read-write
    STATUS      current
    DESCRIPTION
        "Sets the WPA Pre-Shared Key (PSK) used by this service set.  This
         value MUST be either a 64 byte hexadecimal number, OR an 8 to 63
         character ASCII string.
        "
    ::= { cmdot11BssWpaEntry 2 }

cmdot11BssWpaGroupRekeyInterval OBJECT-TYPE
    SYNTAX      Unsigned32
    UNITS       "seconds"
    MAX-ACCESS  read-write
    STATUS      current
    DESCRIPTION
        "Sets the WPA Group Rekey Interval for this service set. If set to zero,
         periodic rekeying is disabled for this service set.
        "
    ::= { cmdot11BssWpaEntry 3 }

-- Objects used to control RADIUS based security modes

cmdot11BssRadiusTable   OBJECT-TYPE
    SYNTAX      SEQUENCE OF Cmdot11BssRadiusEntry
    MAX-ACCESS  not-accessible
    STATUS      current
    DESCRIPTION
        "A table used to configure settings related to the RADIUS security
         modes, including WPA-Enterprise, WPA2-Enterprise and RADIUS-WEP.
        "
    ::= { cmdot11MbssSecurity 5 }

cmdot11BssRadiusEntry OBJECT-TYPE
    SYNTAX      Cmdot11BssRadiusEntry
    MAX-ACCESS  not-accessible
    STATUS      current
    DESCRIPTION
         "An entry defining the RADIUS characteristics of an individual service
          set.  A row exists in this table for each row in the cmdot11BssTable
          for which cmdot11BssSecurityMode is set to wpaEnterprise(4),
          wpa2Enterprise(5), or radiusWep(6).
         "
    INDEX   { ifIndex }
    ::= { cmdot11BssRadiusTable 1 }

Cmdot11BssRadiusEntry ::=
    SEQUENCE    {
                cmdot11BssRadiusAddressType       InetAddressType,
                cmdot11BssRadiusAddress           InetAddress,
                cmdot11BssRadiusPort              Unsigned32,
                cmdot11BssRadiusKey               DisplayString,
                cmdot11BssRadiusReAuthInterval    Unsigned32
    }

cmdot11BssRadiusAddressType OBJECT-TYPE
    SYNTAX      InetAddressType
    MAX-ACCESS  read-write
    STATUS      current
    DESCRIPTION
        "The type of internet address used for cmdot11BssRadiusAddress.
        "
    ::= { cmdot11BssRadiusEntry 1 }

cmdot11BssRadiusAddress OBJECT-TYPE
    SYNTAX      InetAddress
    MAX-ACCESS  read-write
    STATUS      current
    DESCRIPTION
        "The internet address of the RADIUS server for this service set.
        "
    ::= { cmdot11BssRadiusEntry 2 }

cmdot11BssRadiusPort OBJECT-TYPE
    SYNTAX      Unsigned32
    MAX-ACCESS  read-write
    STATUS      current
    DESCRIPTION
        "The UDP port used to communicate with the RADIUS server for this
         service set.
        "
    ::= { cmdot11BssRadiusEntry 3 }

cmdot11BssRadiusKey OBJECT-TYPE
    SYNTAX      DisplayString
    MAX-ACCESS  read-write
    STATUS      current
    DESCRIPTION
        "The RADIUS key.
        "
    ::= { cmdot11BssRadiusEntry 4 }

cmdot11BssRadiusReAuthInterval OBJECT-TYPE
    SYNTAX      Unsigned32
    UNITS       "seconds"
    MAX-ACCESS  read-write
    STATUS      current
    DESCRIPTION
        "The network re-authentication interval.  If set to zero, no
         re-authentication will be performed.
        "
    ::= { cmdot11BssRadiusEntry 5 }

-- Objects used to control WPA factory default setting

cmdot11BssWpaPasscode   OBJECT-TYPE
    SYNTAX      OCTET STRING (SIZE(0..32))
    MAX-ACCESS  read-only
    STATUS      current
    DESCRIPTION
        "The WPA Passcode used to generate the WPA factory default setting.
        "
    ::= { cmdot11MbssSecurity 100 }

--
-- cmdot11MbssAccess contains objects used to configure access restrictions
-- of each service set.
--

cmdot11MbssAccess OBJECT IDENTIFIER ::= { cmdot11MgmtMbss 3 }

cmdot11BssAccessTable  OBJECT-TYPE
    SYNTAX      SEQUENCE OF Cmdot11BssAccessEntry
    MAX-ACCESS  not-accessible
    STATUS      current
    DESCRIPTION
        "A table of MAC addresses which defines the MAC address based access
         restrictions for the system.
        "
    ::= { cmdot11MbssAccess 1 }

cmdot11BssAccessEntry OBJECT-TYPE
    SYNTAX      Cmdot11BssAccessEntry
    MAX-ACCESS  not-accessible
    STATUS      current
    DESCRIPTION
        "A row in the table which specifies a single MAC address for a given
         service set.
        "
    INDEX   { ifIndex, cmdot11BssAccessIndex }
    ::= { cmdot11BssAccessTable 1 }

Cmdot11BssAccessEntry ::=
    SEQUENCE    {
                cmdot11BssAccessIndex       Integer32,
                cmdot11BssAccessStation     PhysAddress,
                cmdot11BssAccessStatus      RowStatus
    }

cmdot11BssAccessIndex OBJECT-TYPE
    SYNTAX      Integer32 (1..16)
    MAX-ACCESS  not-accessible
    STATUS      current
    DESCRIPTION
        "Indicates the instance of this table row.
        "
    ::= { cmdot11BssAccessEntry 1 }

cmdot11BssAccessStation OBJECT-TYPE
    SYNTAX      PhysAddress
    MAX-ACCESS  read-create
    STATUS      current
    DESCRIPTION
        "A MAC address of a station which will be allowed to connect to the
         service set if cmdot11BssAccessMode is set to restrictToList(2), or
         forbidden if cmdot11BssAccessMode is set to denyList(3).
        "
    ::= { cmdot11BssAccessEntry 2 }

cmdot11BssAccessStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         cmdot11BssAccessStatus column is 'notReady'.

         In particular, a newly created row cannot be made active until the
         corresponding instance of cmdot11BssAccessStation has been set.

         Only rows with a status of active(1) will be applied.
        "
    ::= { cmdot11BssAccessEntry 3 }

-- cmdot11ApplySettings: do 'on the fly' config with settings from above.
-- This scalar object was placed by itself at cmdot11plusMgmtv2 100 because
-- it applies all settings from all current and possibly future 802.11
-- groups.  Wanted to leave plenty of room to add new groups in the future.

cmdot11ApplySettings OBJECT-TYPE
    SYNTAX      TruthValue
    MAX-ACCESS  read-write
    STATUS      current
    DESCRIPTION
        "If set to true(1), the wi-fi driver will be restarted using the
         current configuration from non-volatile storage.  This object may be
         used to invoke an immediate reconfiguration of the wi-fi system without
         requiring a full reboot.

         Unless this object is explicitly set to true(1), any settings made via
         other objects in this MIB will be stored to non-volatile storage, but
         will not take effect until the next reboot.

         Always returns false(2) when read.
        "
    ::= { cmdot11plusMgmtv2 100 }

cmdot11ResetToDefaults OBJECT-TYPE
    SYNTAX      TruthValue
    MAX-ACCESS  read-write
    STATUS      current
    DESCRIPTION
        "Setting this object to true(1) causes all the wireless settings
         including Primary and Guest Network settings for all the wi-fi instances to be reset to factory
         defaults.

         Reading this object always returns false(2).
        "
    ::= { cmdot11plusMgmtv2 101 }

cmdot11WpsEnable OBJECT-TYPE
    SYNTAX      TruthValue
    MAX-ACCESS  read-write
    STATUS      current
    DESCRIPTION
        "Setting this object to true(1) enables the Wireless WPS feature.
        Setting this object to false(2) disables the Wireless WPS feature.
        "
    ::= { cmdot11plusWps 1 }

cmdot11WpsMethod OBJECT-TYPE
    SYNTAX      INTEGER
    			{
                 wpsPBC(1),
                 wpsPIN(2)
                }
    MAX-ACCESS  read-write
    STATUS      current
    DESCRIPTION
        "WPS method may be choosen from either Push Button Configuration(1) or Personal Information Number(2).

        if set to wpsPBC(1), user has to push a button, either an actual or virtual one, on both WPS device.
        if set to wpsPIN(2), user has to input a wireless client's PIN on the WPS AP."
    ::= { cmdot11plusWps 2 }

cmdot11WpsPinNumber OBJECT-TYPE
    SYNTAX      Unsigned32
    MAX-ACCESS  read-write
    STATUS      current
    DESCRIPTION
        "Input a wireless client's PIN number to let it be able to register with the WPS AP."
    ::= { cmdot11plusWps 3 }

cmdot11WpsAddClient OBJECT-TYPE
    SYNTAX      TruthValue
    MAX-ACCESS  read-write
    STATUS      current
    DESCRIPTION
        "Setting this object to true(1) starts the Wireless WPS procedure.

        Reading this object always returns false(2).
        "
    ::= { cmdot11plusWps 4 }

cmdot11WlRevInfo OBJECT-TYPE
    SYNTAX      OCTET STRING (SIZE(0..511))
    MAX-ACCESS  read-only
    STATUS      current
    DESCRIPTION
        "This MIB object provides revision information of the wireless card installed on
        the modem. The string includes the vendor id, version identification of the
        hardware and software of the wireless card."
    ::= { cmdot11plusDiag 1 }

cmdot11plusConnectedClientsTable OBJECT-TYPE
    SYNTAX      SEQUENCE OF Cmdot11plusConnectedClientsEntry
    MAX-ACCESS  not-accessible
    STATUS      current
    DESCRIPTION
            "This table contains a list of Wi-Fi connected clients, and associated
             connection information."
    ::= {  cmdot11plusObjects 8 }

cmdot11plusConnectedClientsEntry OBJECT-TYPE
    SYNTAX      Cmdot11plusConnectedClientsEntry
    MAX-ACCESS  not-accessible
    STATUS      current
    DESCRIPTION
            "An entry in the table containing connection information about a connected
             Wi-Fi client"
	INDEX { cmdot11plusClientIndex }
    ::= {  cmdot11plusConnectedClientsTable 1 }

Cmdot11plusConnectedClientsEntry ::= SEQUENCE {
	cmdot11plusClientIndex		INTEGER,
	cmdot11plusClientIpAddr		IpAddress,
	cmdot11plusClientID		MacAddress,
	cmdot11plusClientHostName	OCTET STRING,
	cmdot11plusClientAge		INTEGER,
	cmdot11plusClientMode		INTEGER,
	cmdot11plusClientRssi		INTEGER,
	cmdot11plusClientSpeed		INTEGER,
	cmdot11plusClientConnectedSSID OCTET STRING
    }

cmdot11plusClientIndex OBJECT-TYPE
    SYNTAX	    INTEGER
    MAX-ACCESS	    not-accessible
    STATUS	    current
    DESCRIPTION
	"Table Index"
    ::= {cmdot11plusConnectedClientsEntry 1}

cmdot11plusClientIpAddr OBJECT-TYPE
    SYNTAX      IpAddress
    MAX-ACCESS  read-only
    STATUS      current
    DESCRIPTION
       "The IP Address assigned to the Wi-Fi client."
    ::= { cmdot11plusConnectedClientsEntry 2 }

cmdot11plusClientID OBJECT-TYPE
    SYNTAX      MacAddress
    MAX-ACCESS  read-only
    STATUS      current
    DESCRIPTION
       "The Wi-Fi client's hardware address."
    ::= { cmdot11plusConnectedClientsEntry 3 }

cmdot11plusClientHostName OBJECT-TYPE
    SYNTAX      OCTET STRING
    MAX-ACCESS  read-only
    STATUS      current
    DESCRIPTION
       "The Host Name of the Wi-Fi client, derived from DHCP option 12."
    ::= { cmdot11plusConnectedClientsEntry 4 }

cmdot11plusClientAge OBJECT-TYPE
    SYNTAX      INTEGER
    MAX-ACCESS  read-only
    STATUS      current
    DESCRIPTION
       "Elapsed time in seconds since the last IP packet was received
        from or sent to the Wi-Fi client."
    ::= { cmdot11plusConnectedClientsEntry 5 }

cmdot11plusClientMode OBJECT-TYPE
    SYNTAX      INTEGER{
                a(1),
                g(2),
                n(3)
    }
    MAX-ACCESS  read-only
    STATUS      current
    DESCRIPTION
       "The connection mode of the Wi-Fi client."
    ::= { cmdot11plusConnectedClientsEntry 6 }

cmdot11plusClientRssi OBJECT-TYPE
    SYNTAX      INTEGER
    MAX-ACCESS  read-only
    STATUS      current
    DESCRIPTION
       "The Wi-Fi client's Received Signal Strength in dBm."
    ::= { cmdot11plusConnectedClientsEntry 7 }

cmdot11plusClientSpeed OBJECT-TYPE
    SYNTAX      INTEGER
    MAX-ACCESS  read-only
    STATUS      current
    DESCRIPTION
       "The Wi-Fi client's connected link speed."
    ::= { cmdot11plusConnectedClientsEntry 8 }

cmdot11plusClientConnectedSSID OBJECT-TYPE
    SYNTAX      OCTET STRING
    MAX-ACCESS  read-only
    STATUS      current
    DESCRIPTION
       "The SSID (Service Set Identifier) to which the Wi-Fi client is connected."
    ::= { cmdot11plusConnectedClientsEntry 9 }

cmdot11wifiHotspotEnabled OBJECT-TYPE
    SYNTAX      TruthValue
    MAX-ACCESS  read-write
    STATUS      current
    DESCRIPTION
        "Enables or disable Wifi Hotspot support in the device."
   ::= { cmdot11wifiHotspotBase 1 }

cmdot11wifiHotspotTable   OBJECT-TYPE
    SYNTAX      SEQUENCE OF Cmdot11wifiHotspotIfEntry
    MAX-ACCESS  not-accessible
    STATUS      current
    DESCRIPTION
        "A table used to configure settings related to Wi-fi Hotspot."
    ::= { cmdot11wifiHotspotBase 2 }

cmdot11wifiHotspotIfEntry OBJECT-TYPE
    SYNTAX      Cmdot11wifiHotspotIfEntry
    MAX-ACCESS  not-accessible
    STATUS      current
    DESCRIPTION
         "An entry defining the Wi-fi hotspot characteristics of an
          individual Wi-Fi network interface."
    INDEX   { cmdot11wifiHotspotIf }
    ::= { cmdot11wifiHotspotTable 1 }

Cmdot11wifiHotspotIfEntry ::=
    SEQUENCE    {
        cmdot11wifiHotspotInstance              Unsigned32,
        cmdot11wifiHotspotIf                    INTEGER,
        cmdot11wifiHotspotMode                  INTEGER,
        cmdot11wifiHotspotCpeIdleTimeout        Unsigned32,
        cmdot11wifiHotspotCpeSessionTimeout     Unsigned32,
        cmdot11wifiHotspotRadiusAccAddressType  InetAddressType,
        cmdot11wifiHotspotRadiusAccAddress      InetAddress,
        cmdot11wifiHotspotRadiusAccPort         InetPortNumber,
        cmdot11wifiHotspotRadiusAccKey          DisplayString,
        cmdot11wifiHotspotPacketFilterMask      Unsigned32,
        cmdot11wifiHotspotInsertDhcpOptionsMask Unsigned32,
        cmdot11wifiHotspotRowStatus             RowStatus
    }

cmdot11wifiHotspotInstance    OBJECT-TYPE
    SYNTAX      Unsigned32
    MAX-ACCESS  not-accessible
    STATUS      current
    DESCRIPTION
        "The key for a unique instance of this object."
    ::= { cmdot11wifiHotspotIfEntry 1 }

cmdot11wifiHotspotIf OBJECT-TYPE
    SYNTAX      INTEGER {
                        wifi1-0(1),
                        wifi1-1(2),
                        wifi1-2(3),
                        wifi1-3(4),
                        wifi1-4(5),
                        wifi1-5(6),
                        wifi1-6(7),
                        wifi1-7(8),
                        wifi2-0(9),
                        wifi2-1(10),
                        wifi2-2(11),
                        wifi2-3(12),
                        wifi2-4(13),
                        wifi2-5(14),
                        wifi2-6(15),
                        wifi2-7(16)
        }
    MAX-ACCESS  read-create
    STATUS      current
    DESCRIPTION
        "Wi-fi network interface."
    ::= { cmdot11wifiHotspotIfEntry 2 }

cmdot11wifiHotspotMode OBJECT-TYPE
    SYNTAX      INTEGER {
                disable(1),
                enableBridge(2),
                enableCmdot11l2ogre(3)
    }
    MAX-ACCESS  read-create
    STATUS      current
    DESCRIPTION
        "Wi-fi Hotsot mode:
         enableBridge - Wi-Fi traffic will be bridged
         enableCmdot11l2ogre - Wi-Fi traffic will be sent over GRE tunnel.
                        GRE Tunnel should be configured and enabled."
    ::= { cmdot11wifiHotspotIfEntry 3 }

cmdot11wifiHotspotCpeIdleTimeout OBJECT-TYPE
    SYNTAX      Unsigned32
    MAX-ACCESS  read-create
    STATUS      current
    DESCRIPTION
        "CPE inactivity/idle timeout in seconds which will trigger disconnect.
         Value of 0 will disable inactivity tracking."
    ::= { cmdot11wifiHotspotIfEntry 4 }

cmdot11wifiHotspotCpeSessionTimeout OBJECT-TYPE
    SYNTAX      Unsigned32
    MAX-ACCESS  read-create
    STATUS      current
    DESCRIPTION
        "CPE maximum session duration timeout in seconds.
         Value of 0 will disable tracking session duration."
    ::= { cmdot11wifiHotspotIfEntry 5 }

cmdot11wifiHotspotRadiusAccAddressType OBJECT-TYPE
    SYNTAX      InetAddressType
    MAX-ACCESS  read-create
    STATUS      current
    DESCRIPTION
        "The type of internet address used for cmdot11wifiHotspotRadiusAccAddress."
    ::= { cmdot11wifiHotspotIfEntry 6 }

cmdot11wifiHotspotRadiusAccAddress OBJECT-TYPE
    SYNTAX      InetAddress
    MAX-ACCESS  read-create
    STATUS      current
    DESCRIPTION
        "The internet address of the RADIUS Accounting server for this service set."
    ::= { cmdot11wifiHotspotIfEntry 7 }

cmdot11wifiHotspotRadiusAccPort OBJECT-TYPE
    SYNTAX      InetPortNumber
    MAX-ACCESS  read-create
    STATUS      current
    DESCRIPTION
        "The UDP port used to communicate with the RADIUS Accounting server.
         Default value set to 1813."
    ::= { cmdot11wifiHotspotIfEntry 8 }

cmdot11wifiHotspotRadiusAccKey OBJECT-TYPE
    SYNTAX      DisplayString
    MAX-ACCESS  read-create
    STATUS      current
    DESCRIPTION
        "The RADIUS Accounting server shared security key."
    ::= { cmdot11wifiHotspotIfEntry 9 }

cmdot11wifiHotspotPacketFilterMask OBJECT-TYPE
    SYNTAX      Unsigned32
    MAX-ACCESS  read-create
    STATUS      current
    DESCRIPTION
        "Bit mask for limiting traffic to certain packet types.
         Possible value:
         11111111 11111111 11111111 11111111: Allow All traffic
         xxxxxxxx xxxxxxxx xxxxxxxx xxxxxxx1: Allow IPv4 (0x0800) packets
         xxxxxxxx xxxxxxxx xxxxxxxx xxxxxx1x: Allow IPv6 (0x86dd) packets
         xxxxxxxx xxxxxxxx xxxxxxxx xxxxx1xx: Allow IPx  (0x8137) packets
         xxxxxxxx xxxxxxxx xxxxxxxx xxxx1xxx: Allow ARP  (0x0806) packets
         xxxxxxxx xxxxxxxx xxxxxxxx xxx1xxxx: Allow RARP (0x8035) packets
         xxxxxxxx xxxxxxxx xxxxxxxx xx1xxxxx: Allow VLAN (0x8100) packets
         xxxxxxxx xxxxxxxx xxxxxxx1 xxxxxxxx: Allow Broadcast packets in DS
         xxxxxxxx xxxxxxxx xxxxxx1x xxxxxxxx: Allow Broadcast packets in US
         xxxxxxxx xxxxxxxx xxxxx1xx xxxxxxxx: Allow Multicast packets in DS
         xxxxxxxx xxxxxxxx xxxx1xxx xxxxxxxx: Allow Multicast packets in US
         "
    ::= { cmdot11wifiHotspotIfEntry 10 }

cmdot11wifiHotspotInsertDhcpOptionsMask OBJECT-TYPE
    SYNTAX      Unsigned32
    MAX-ACCESS  read-create
    STATUS      current
    DESCRIPTION
        "Bit mask for inserting DHCP options in DHCP Discover/Request packet from
         connected wifi client device.
         Possible value:
         0x1: Insert DHCP relay agent option 82.
              circuit-id sub-option: AP-MAC-ADDRESS;SSID-NAME;SSID-TYPE
         0x2: Insert DHCP relay agent option 82.
              remote-id  sub-option: String containing MAC address of connected
                                     wifi client device in the format XX:XX:XX:XX:XX:XX.
         0x4: Insert/Modify DHCP option 60 with string containing SSID Name."
    ::= { cmdot11wifiHotspotIfEntry 11 }

cmdot11wifiHotspotRowStatus OBJECT-TYPE
    SYNTAX RowStatus
    MAX-ACCESS read-create
    STATUS current
    DESCRIPTION
        "The RowStatus interlock for the creation and deletion
        can be modified at any time while the row is active(1)."
    ::= { cmdot11wifiHotspotIfEntry 12 }

cmdot11wifiHotspotAutRateLimit OBJECT-TYPE
    SYNTAX      Unsigned32
    MAX-ACCESS  read-write
    STATUS      current
    DESCRIPTION
        "Authentication rate limit in messages per second. If client exceeds
         this limit, authentication from the client is ignored for
         cmdot11wifiHotspotAutDenialTimeout."
   ::= { cmdot11wifiHotspotBase 3 }

cmdot11wifiHotspotAutDenialTimeout OBJECT-TYPE
    SYNTAX      Unsigned32
    MAX-ACCESS  read-write
    STATUS      current
    DESCRIPTION
        "Timeout in seconds during which authentication from a client is ignored
         once authentication message rate exceeds cmdot11wifiHotspotAutRateLimit."
   ::= { cmdot11wifiHotspotBase 4 }

cmdot11wifiHotspotRadiusOrigIf OBJECT-TYPE
    SYNTAX      INTEGER {
                eRouter(1),
                cm(2)
        }
    MAX-ACCESS  read-write
    STATUS      current
    DESCRIPTION
        "Originating interface of radius authentication and accounting traffic."
    ::= { cmdot11wifiHotspotBase 5 }

cmdot11wifiHotspotIgnoreMaxCpeSetting OBJECT-TYPE
    SYNTAX      TruthValue
    MAX-ACCESS  read-write
    STATUS      current
    DESCRIPTION
        "This setting is applicable for wifi hotspot bridged mode.
         When set to true(1), clients connected through the hotspot wifi will not be
         counted when enforcing the 'Maximum CPE devices' on DOCSIS."
   ::= { cmdot11wifiHotspotBase 6 }

cmdot11wifiHotspotDisablePMKCaching OBJECT-TYPE
    SYNTAX      TruthValue
    MAX-ACCESS  read-write
    STATUS      current
    DESCRIPTION
        "Enables or disable WPA2 PMK Caching."
   ::= { cmdot11wifiHotspotBase 7 }

cmdot11wifiHotspotConnectionSpeedMin OBJECT-TYPE
    SYNTAX      Unsigned32
    MAX-ACCESS  read-write
    STATUS      current
    DESCRIPTION
        "Minimum connection speed in kbps required by client to maintain connectivity."
   ::= { cmdot11wifiHotspotBase 8 }

cmdot11wifiHotspotConnectionSpeedTimeout OBJECT-TYPE
    SYNTAX      Unsigned32
    MAX-ACCESS  read-write
    STATUS      current
    DESCRIPTION
        "Timeout in seconds during which client is allowed to maintain connectivity
         once connection speed is below cmdot11wifiHotspotConnectionSpeedMin. When timeout
         expires client is disassociated."
   ::= { cmdot11wifiHotspotBase 9 }




cmdot11l2ogreEnabled OBJECT-TYPE
    SYNTAX      TruthValue
    MAX-ACCESS  read-write
    STATUS      current
    DESCRIPTION
        "Enables or disable GRE Tunnel support in the device."
   ::= { cmdot11l2ogreBase 1 }

cmdot11l2ogrePriRemoteAddressType OBJECT-TYPE
    SYNTAX      InetAddressType
    MAX-ACCESS  read-write
    STATUS      current
    DESCRIPTION
        "The IP address type (ipv4, ipv6 or dns) of primary remote
         endpoint of the GRE tunnel."
    DEFVAL { ipv4 }
    ::= { cmdot11l2ogreBase 2 }

cmdot11l2ogrePriRemoteAddress OBJECT-TYPE
    SYNTAX      InetAddress
    MAX-ACCESS  read-write
    STATUS      current
    DESCRIPTION
        "IP address or FQDN of primary remote endpoint of the GRE tunnel."
    ::= { cmdot11l2ogreBase 3 }

cmdot11l2ogreSecRemoteAddressType OBJECT-TYPE
    SYNTAX      InetAddressType
    MAX-ACCESS  read-write
    STATUS      current
    DESCRIPTION
        "The IP address type (ipv4, ipv6 or dns) of secondary remote
         endpoint of the GRE tunnel."
    DEFVAL { ipv4 }
    ::= { cmdot11l2ogreBase 4 }

cmdot11l2ogreSecRemoteAddress OBJECT-TYPE
    SYNTAX      InetAddress
    MAX-ACCESS  read-write
    STATUS      current
    DESCRIPTION
        "IP address or FQDN of secondary remote endpoint of the GRE tunnel."
    ::= { cmdot11l2ogreBase 5 }

cmdot11l2ogreDSCP OBJECT-TYPE
    SYNTAX      Integer32 (0..63)
    MAX-ACCESS  read-write
    STATUS      current
    DESCRIPTION
        "The method is used to set the high 6 bits of TOS in the
         IPv4 header or traffic class in IPv6 header."
    ::= { cmdot11l2ogreBase 6 }

cmdot11l2ogreKeepAliveMode OBJECT-TYPE
    SYNTAX      INTEGER {
                disabled(1),
                ping(2),
                ping-noswitchover(3)
    }
    MAX-ACCESS  read-write
    STATUS      current
    DESCRIPTION
        "Keepalive modes for failover mechanism.
         ping - Use ICMP pings within tunnel as a keepalive messages."
    ::= { cmdot11l2ogreBase 7 }

cmdot11l2ogreKeepAliveCount OBJECT-TYPE
    SYNTAX      Integer32
    MAX-ACCESS  read-write
    STATUS      current
    DESCRIPTION
        "Number of keep-alive messages sent at regular interval."
    ::= { cmdot11l2ogreBase 8 }

cmdot11l2ogreKeepAliveInterval OBJECT-TYPE
    SYNTAX      Integer32
    MAX-ACCESS  read-write
    STATUS      current
    DESCRIPTION
        "Interval in seconds between keep-alive messages."
    ::= { cmdot11l2ogreBase 9 }

cmdot11l2ogreKeepAliveFailureThreshold OBJECT-TYPE
    SYNTAX      Integer32
    MAX-ACCESS  read-write
    STATUS      current
    DESCRIPTION
        "Number of keep-alive failures that will cause fail-over."
    ::= { cmdot11l2ogreBase 10 }

cmdot11l2ogreStatsTable OBJECT-TYPE
    SYNTAX      SEQUENCE OF Cmdot11l2ogreStatsEntry
    MAX-ACCESS  not-accessible
    STATUS      current
    DESCRIPTION
        "This table provides statistical information of GRE tunnel."
    ::= { cmdot11l2ogreBase 11 }

cmdot11l2ogreStatsEntry OBJECT-TYPE
    SYNTAX      Cmdot11l2ogreStatsEntry
    MAX-ACCESS  not-accessible
    STATUS      current
    DESCRIPTION
        "This table provides statistical information of GRE tunnel."
    INDEX { cmdot11l2ogreStatsIndex }
    ::= { cmdot11l2ogreStatsTable 1 }

Cmdot11l2ogreStatsEntry ::= SEQUENCE {
    cmdot11l2ogreStatsIndex                    Integer32,
    cmdot11l2ogreStatsBytesSent                Counter64,
    cmdot11l2ogreStatsBytesReceived            Counter64,
    cmdot11l2ogreStatsPacketsSent              Counter64,
    cmdot11l2ogreStatsPacketsReceived          Counter64,
    cmdot11l2ogreStatsDiscardPacketsReceived   Counter64,
    cmdot11l2ogreStatsErrorPacketsReceived     Counter64,
    cmdot11l2ogreStatsKeepAliveSent            Counter64,
    cmdot11l2ogreStatsKeepAliveReceived        Counter64,
    cmdot11l2ogreStatsRowStatus                RowStatus
}

cmdot11l2ogreStatsIndex OBJECT-TYPE
    SYNTAX      Integer32 (1..256)
    MAX-ACCESS  not-accessible
    STATUS      current
    DESCRIPTION
        "Table index"
    ::= { cmdot11l2ogreStatsEntry 1 }

cmdot11l2ogreStatsBytesSent OBJECT-TYPE
    SYNTAX      Counter64
    MAX-ACCESS  read-only
    STATUS      current
    DESCRIPTION
        "Number bytes sent."
    ::= { cmdot11l2ogreStatsEntry 2 }

cmdot11l2ogreStatsBytesReceived OBJECT-TYPE
    SYNTAX      Counter64
    MAX-ACCESS  read-only
    STATUS      current
    DESCRIPTION
        "Number bytes received."
    ::= { cmdot11l2ogreStatsEntry 3 }

cmdot11l2ogreStatsPacketsSent OBJECT-TYPE
    SYNTAX      Counter64
    MAX-ACCESS  read-only
    STATUS      current
    DESCRIPTION
        "Number packets sent."
    ::= { cmdot11l2ogreStatsEntry 4 }

cmdot11l2ogreStatsPacketsReceived OBJECT-TYPE
    SYNTAX      Counter64
    MAX-ACCESS  read-only
    STATUS      current
    DESCRIPTION
        "Number packets received."
    ::= { cmdot11l2ogreStatsEntry 5 }

cmdot11l2ogreStatsDiscardPacketsReceived OBJECT-TYPE
    SYNTAX      Counter64
    MAX-ACCESS  read-only
    STATUS      current
    DESCRIPTION
        "Number packets received that were discarded.
         Because source network interface is down."
    ::= { cmdot11l2ogreStatsEntry 6 }

cmdot11l2ogreStatsErrorPacketsReceived OBJECT-TYPE
    SYNTAX      Counter64
    MAX-ACCESS  read-only
    STATUS      current
    DESCRIPTION
        "Number packets received that were in error.
         Because tunnel packets are not correct type.
         Eg. Received IP packet instead of L2 packets."
    ::= { cmdot11l2ogreStatsEntry 7 }

cmdot11l2ogreStatsKeepAliveSent OBJECT-TYPE
    SYNTAX      Counter64
    MAX-ACCESS  read-only
    STATUS      current
    DESCRIPTION
        "Number keepalive packets sent."
    ::= { cmdot11l2ogreStatsEntry 8 }

cmdot11l2ogreStatsKeepAliveReceived OBJECT-TYPE
    SYNTAX      Counter64
    MAX-ACCESS  read-only
    STATUS      current
    DESCRIPTION
        "Number keepalive packets received."
    ::= { cmdot11l2ogreStatsEntry 9 }

cmdot11l2ogreStatsRowStatus OBJECT-TYPE
    SYNTAX RowStatus
    MAX-ACCESS read-create
    STATUS current
    DESCRIPTION
        "The RowStatus interlock for the creation and deletion
        can be modified at any time while the row is active(1)."
    ::= { cmdot11l2ogreStatsEntry 10 }

cmdot11l2ogreSourceIfTable OBJECT-TYPE
    SYNTAX      SEQUENCE OF Cmdot11l2ogreSourceIfEntry
    MAX-ACCESS  not-accessible
    STATUS      current
    DESCRIPTION
        "This table contains information specific to network source interface
         whose traffic is mapped into GRE tunnel."
    ::= { cmdot11l2ogreBase 12 }

cmdot11l2ogreSourceIfEntry OBJECT-TYPE
    SYNTAX      Cmdot11l2ogreSourceIfEntry
    MAX-ACCESS  not-accessible
    STATUS      current
    DESCRIPTION
        "List of individual source interface entries mapped into GRE tunnel."
    INDEX { cmdot11l2ogreSourceIfInstance }
    ::= { cmdot11l2ogreSourceIfTable 1 }

Cmdot11l2ogreSourceIfEntry ::= SEQUENCE {
    cmdot11l2ogreSourceIfInstance           Unsigned32,
    cmdot11l2ogreSourceIf                   INTEGER,
    cmdot11l2ogreSourceIfEnabled            TruthValue,
    cmdot11l2ogreSourceIfVlanTag            Integer32,
    cmdot11l2ogreSourceIfMplsHeader         Integer32,
    cmdot11l2ogreSourceIfRowStatus          RowStatus
}

cmdot11l2ogreSourceIfInstance    OBJECT-TYPE
    SYNTAX      Unsigned32
    MAX-ACCESS  not-accessible
    STATUS      current
    DESCRIPTION
        "The key for a unique instance of this object."
    ::= {cmdot11l2ogreSourceIfEntry 1 }

cmdot11l2ogreSourceIf OBJECT-TYPE
    SYNTAX      INTEGER {
                        wifi1-0(1),
                        wifi1-1(2),
                        wifi1-2(3),
                        wifi1-3(4),
                        wifi1-4(5),
                        wifi1-5(6),
                        wifi1-6(7),
                        wifi1-7(8),
                        wifi2-0(9),
                        wifi2-1(10),
                        wifi2-2(11),
                        wifi2-3(12),
                        wifi2-4(13),
                        wifi2-5(14),
                        wifi2-6(15),
                        wifi2-7(16)
        }
    MAX-ACCESS  read-create
    STATUS      current
    DESCRIPTION
        "Source interface whose traffic will be pass through GRE tunnel."
    ::= { cmdot11l2ogreSourceIfEntry 2 }

cmdot11l2ogreSourceIfEnabled OBJECT-TYPE
    SYNTAX      TruthValue
    MAX-ACCESS  read-create
    STATUS      current
    DESCRIPTION
        "Enables or disable mapping traffic from network interface into GRE tunnel."
   ::= { cmdot11l2ogreSourceIfEntry 3 }

cmdot11l2ogreSourceIfVlanTag OBJECT-TYPE
    SYNTAX      Integer32
    MAX-ACCESS  read-create
    STATUS      current
    DESCRIPTION
        "Add VLAN tag consists of 16bit of Tag Protocol Identifier (TPID)
         and 16 bit of Tag Control Identifier (TCI).
         Value of 0 will disable adding VLAN tag.
         Tag Protocol Identifier (TPID) should set to 0x8100."
    ::= { cmdot11l2ogreSourceIfEntry 4 }

cmdot11l2ogreSourceIfMplsHeader OBJECT-TYPE
    SYNTAX      Integer32
    MAX-ACCESS  read-create
    STATUS      current
    DESCRIPTION
        "MPLS Header. Value of 0 will disable adding MPLS Header."
    ::= { cmdot11l2ogreSourceIfEntry 5 }

cmdot11l2ogreSourceIfRowStatus OBJECT-TYPE
    SYNTAX      RowStatus
    MAX-ACCESS  read-create
    STATUS      current
    DESCRIPTION
        "The RowStatus interlock for the creation and deletion of a table entry."
    ::= { cmdot11l2ogreSourceIfEntry 6 }

cmdot11l2ogreOrigIf OBJECT-TYPE
    SYNTAX      INTEGER {
                eRouter(1)
        }
    MAX-ACCESS  read-write
    STATUS      current
    DESCRIPTION
        "Originating Interface of GRE tunnel."
    ::= { cmdot11l2ogreBase 13 }

cmdot11l2ogreConcentratorServiceName OBJECT-TYPE
    SYNTAX      DisplayString
    MAX-ACCESS  read-write
    STATUS      current
    DESCRIPTION
        "FQDN of GRE tunnel concentrator/gw service.
         If this is set then, DNS Query of type SRV will be used for discovering
         FQDN of primary and secondary remote endpoint of GRE tunnel."
    ::= { cmdot11l2ogreBase 14 }

cmdot11l2ogreDnsResolverRetryTimerMin OBJECT-TYPE
    SYNTAX      Unsigned32
    MAX-ACCESS  read-write
    STATUS      current
    DESCRIPTION
        "Minimum timeout interval in seconds before retrying DNS query."
    ::= { cmdot11l2ogreBase 15 }

cmdot11l2ogreDnsResolverRetryTimerMax OBJECT-TYPE
    SYNTAX      Unsigned32
    MAX-ACCESS  read-write
    STATUS      current
    DESCRIPTION
        "Maximum timeout interval in seconds before retrying DNS query."
    ::= { cmdot11l2ogreBase 16 }

END
