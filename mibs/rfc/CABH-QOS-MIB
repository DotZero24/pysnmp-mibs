CABH-QOS-MIB DEFINITIONS ::= BEGIN
   IMPORTS
      MODULE-IDENTITY,
      OBJECT-TYPE,
      Unsigned32
                               FROM SNMPv2-SMI

      TruthValue,
      RowStatus                FROM SNMPv2-TC

      OBJECT-GROUP,
      MODULE-COMPLIANCE        FROM SNMPv2-CONF

      InetPortNumber,
      InetAddressType,
      InetAddress              FROM INET-ADDRESS-MIB

      ifIndex                  FROM IF-MIB

-- CL specs releases before RFC
      clabProjCableHome	    	FROM CLAB-DEF-MIB;

   cabhQosMib MODULE-IDENTITY
       LAST-UPDATED    "200303010000Z" -- March 1, 2003
       ORGANIZATION    "CableLabs Broadband Access Department"
       CONTACT-INFO
            "Kevin Luehrs
             Postal: Cable Television Laboratories, Inc.
             400 Centennial Parkway
             Louisville, Colorado 80027-1266
             U.S.A.
             Phone:  +1 303-661-9100
             Fax:    +1 303-661-9199
             E-mail: k.luehrs@cablelabs.com; mibs@cablelabs.com"
       DESCRIPTION
               "This MIB module supplies parameters for the
                configuration and monitoring of CableHome
                prioritized QoS capability."
       REVISION "200303010000Z" -- March 1, 2003
       DESCRIPTION
               "Initial version, published as RFC xxxx."
                -- RFC editor to assign xxxx
--    ::= { mib-2 xx }
-- xx to be assigned by IANA
-- CL specs releases before RFC
    ::=  { clabProjCableHome 6 }

   -- Textual conventions

   cabhQosMibObjects         OBJECT IDENTIFIER ::= { cabhQosMib 1}
   cabhPriorityQosMibObjects OBJECT IDENTIFIER ::= { cabhQosMibObjects 1 }
   cabhPriorityQosBase       OBJECT IDENTIFIER ::= { cabhPriorityQosMibObjects 1 }
   cabhPriorityQosBp         OBJECT IDENTIFIER ::= { cabhPriorityQosMibObjects 2 }
   cabhPriorityQosPs         OBJECT IDENTIFIER ::= { cabhPriorityQosMibObjects 3 }

   -- future parametric QOS
   -- cabhParamQosMibObjects  OBJECT IDENTIFIER ::= { cabhQosMibObjects 2 }

   --=================================================================
   --
   --  Application Priority Master Table
   --
   --  The cabhPriorityQosMasterTable contains the list of
   --  application priorities provisioned by the cable operator.
   --  Applications are identified by the IANA "well-known" port
   --  numbers  assigned to them.
   --
   --==================================================================
   cabhPriorityQosMasterTable  OBJECT-TYPE
         SYNTAX SEQUENCE OF CabhPriorityQosMasterEntry
         MAX-ACCESS  not-accessible
         STATUS      current
         DESCRIPTION
           "This table contains a list of mappings for Application
            IDs to Default CableHome Priorities."
         ::= { cabhPriorityQosBase 1  }

   cabhPriorityQosMasterEntry OBJECT-TYPE
           SYNTAX CabhPriorityQosMasterEntry
           MAX-ACCESS   not-accessible
           STATUS    current
           DESCRIPTION
             "An entry for mapping Application IDs to
             Default CableHome Priorities."
      INDEX { cabhPriorityQosMasterApplicationId }
      ::= { cabhPriorityQosMasterTable 1 }


   CabhPriorityQosMasterEntry ::= SEQUENCE {
         cabhPriorityQosMasterApplicationId       Unsigned32,
         cabhPriorityQosMasterDefaultCHPriority   Unsigned32,
         cabhPriorityQosMasterRowStatus           RowStatus
        }

   cabhPriorityQosMasterApplicationId       OBJECT-TYPE
       SYNTAX                  Unsigned32 (1..65535)
       MAX-ACCESS              not-accessible
       STATUS                  current
       DESCRIPTION
        "The IANA well-known port number identifying an application."
       ::= { cabhPriorityQosMasterEntry 1 }


   cabhPriorityQosMasterDefaultCHPriority       OBJECT-TYPE
       SYNTAX                  Unsigned32 (0..7)
       MAX-ACCESS              read-create
       STATUS                  current
       DESCRIPTION
        "The Qos priority assigned to the application."
       ::= { cabhPriorityQosMasterEntry 2 }

   cabhPriorityQosMasterRowStatus  OBJECT-TYPE
       SYNTAX                  RowStatus
       MAX-ACCESS              read-create
       STATUS                  current
       DESCRIPTION
         "The Row Status interlock for creation and deletion
          of row entries. The PS MUST NOT allow the NMS to
          set RowStatus to notInService(2). The PS MUST assign a
          RowStatus of notReady(3) to any new row created
          without a valid value for both entries. The PS will
          prevent modification of this table's columns and return
          an inconsistentValue error if the NMS attempts to make
          such modifications while RowStatus is active(1)."
       ::= { cabhPriorityQosMasterEntry 3 }



   -- =================================================================
   --
   --  SetToFactory Object
   --
   -- This object is used to clear some of the QoS MIB tables
   --
   -- ==================================================================

cabhPriorityQosSetToFactory OBJECT-TYPE
       SYNTAX TruthValue
       MAX-ACCESS read-write
       STATUS current
       DESCRIPTION
         "Reading this object alwyas returns false(2). When this object is
          set to true(1), the PS MUST  clear all the entries in the
          cabhPriorityQosBpTable and cabhPriorityQosBpDestTable."

       ::= { cabhPriorityQosBase 2 }


   --===============================================================
   --
   --  BP Application Priority Table
   --
   --  The cabhPriorityQosBpTable contains the list of
   --  BPs, the applications implemented on each, and the priority
   --  assigned to each application.
   --
   --===============================================================

   cabhPriorityQosBpTable OBJECT-TYPE
      SYNTAX SEQUENCE OF CabhPriorityQosBpEntry
      MAX-ACCESS not-accessible
      STATUS current
      DESCRIPTION
         "This table contains the priorities for each of the
          discovered CableHome Host (BP) applications
          and related data."
            ::= {cabhPriorityQosBp 1}

   cabhPriorityQosBpEntry OBJECT-TYPE
      SYNTAX      CabhPriorityQosBpEntry
      MAX-ACCESS     not-accessible
      STATUS      current
      DESCRIPTION
         "List of all the discovered applications on a BP
          and their priorities identified by the PS."
      INDEX { cabhPriorityQosMasterApplicationId,
              cabhPriorityQosBpIpAddrType, cabhPriorityQosBpIpAddr }
      ::= { cabhPriorityQosBpTable 1 }

   CabhPriorityQosBpEntry ::= SEQUENCE {
         cabhPriorityQosBpIpAddrType         InetAddressType,
         cabhPriorityQosBpIpAddr             InetAddress,
         cabhPriorityQosBpApplicationId      Unsigned32,
         cabhPriorityQosBpDefaultCHPriority  Unsigned32,
         cabhPriorityQosBpIndex              Unsigned32
         }

   cabhPriorityQosBpIpAddrType   OBJECT-TYPE
      SYNTAX      InetAddressType
      MAX-ACCESS  read-only
      STATUS      current
      DESCRIPTION
         "The type of the IP address assigned to a particular
          BP element."
      ::= { cabhPriorityQosBpEntry 1 }


   cabhPriorityQosBpIpAddr    OBJECT-TYPE
      SYNTAX      InetAddress
      MAX-ACCESS  read-only
      STATUS      current
      DESCRIPTION
         "The IP address assigned to a particular BP element."
      ::= { cabhPriorityQosBpEntry 2 }

   cabhPriorityQosBpApplicationId   OBJECT-TYPE
      SYNTAX      Unsigned32 (1..65535)
      MAX-ACCESS  read-only
      STATUS      current
      DESCRIPTION
         "The IANA well-known port number assigned to a
          particular application implemented on the
          CableHome Host device in which this BP resides."
      ::= { cabhPriorityQosBpEntry 3 }


   cabhPriorityQosBpDefaultCHPriority  OBJECT-TYPE
      SYNTAX      Unsigned32 (0..7)
      MAX-ACCESS  read-only
      STATUS      current
      DESCRIPTION
         "The priority assigned to a particular application
          implemented on CableHome Host device in which this
          BP resides. The PS populates this entry according
          to the Application Priority Master Table."
      ::= { cabhPriorityQosBpEntry 4 }

   cabhPriorityQosBpIndex  OBJECT-TYPE
      SYNTAX      Unsigned32 (1..65535)
      MAX-ACCESS  read-only
      STATUS      current
      DESCRIPTION
        "The unique identifier for a particular row in the
         BP Application Priority Table. This identifier is
         used as an index into the 'nested' Destination
         Priority Table."
           ::= { cabhPriorityQosBpEntry 5 }


   --===============================================================
   --
   --  Destination Priority Table
   --
   --  The cabhPriorityQosDestListTable contains the list of
   --  provisioned destinations (IP address and port number) to
   --  which a BP can send traffic with a special Qos
   --  priority. Any application listed in the BP Application
   --  Priority Table can be provisioned with a destination specific
   --  priority in this table.
   --
   --===============================================================

   cabhPriorityQosBpDestTable OBJECT-TYPE
      SYNTAX SEQUENCE OF CabhPriorityQosBpDestEntry
      MAX-ACCESS     not-accessible
      STATUS      current
      DESCRIPTION
         "This table contains the priorities based on
          sessions established by a BP, identified by
          destination IP address and port number. It
          is indexed with a unique identifier for rows
          in the BP Application Priority Table
          (cabhPriorityQoSBpTable."
          ::= {cabhPriorityQosBp 2}

   cabhPriorityQosBpDestEntry OBJECT-TYPE
      SYNTAX      CabhPriorityQosBpDestEntry
      MAX-ACCESS  not-accessible
      STATUS      current
      DESCRIPTION
         "List of Destination IP addresses and port numbers
          for an application to which special Qos
          priority is provisioned."
      INDEX { cabhPriorityQosBpIndex, cabhPriorityQosBpDestIndex }
      ::= { cabhPriorityQosBpDestTable 1 }

   CabhPriorityQosBpDestEntry ::= SEQUENCE {
       cabhPriorityQosBpDestIndex            Unsigned32,
       cabhPriorityQosBpDestIpAddrType       InetAddressType,
       cabhPriorityQosBpDestIpAddr           InetAddress,
       cabhPriorityQosBpDestPort             InetPortNumber,
       cabhPriorityQosBpDestIpPortPriority   Unsigned32
         }


   cabhPriorityQosBpDestIndex OBJECT-TYPE
      SYNTAX      Unsigned32 (1..65535)
      MAX-ACCESS  not-accessible
      STATUS      current
      DESCRIPTION
        "The locally unique index into the Destination
         Priority Table."
      ::= { cabhPriorityQosBpDestEntry 1 }

   cabhPriorityQosBpDestIpAddrType     OBJECT-TYPE
      SYNTAX      InetAddressType
      MAX-ACCESS  read-only
      STATUS      current
      DESCRIPTION
         "The type of the Destination IP Address."
      ::= { cabhPriorityQosBpDestEntry 2 }

   cabhPriorityQosBpDestIpAddr   OBJECT-TYPE
      SYNTAX      InetAddress
      MAX-ACCESS  read-only
      STATUS      current
      DESCRIPTION
        "The Destination IP address of the device to which
         an application-session is established by a BP and
         a special Qos priority is provisioned."
      ::= { cabhPriorityQosBpDestEntry 3 }

   cabhPriorityQosBpDestPort     OBJECT-TYPE
      SYNTAX      InetPortNumber
      MAX-ACCESS  read-only
      STATUS      current
      DESCRIPTION
        "The port number on a IP device to which
         an application-session is established by a BP and
         a special Qos priority is provisioned."
      ::= { cabhPriorityQosBpDestEntry 4 }

   cabhPriorityQosBpDestIpPortPriority    OBJECT-TYPE
      SYNTAX      Unsigned32 (0..7)
      MAX-ACCESS  read-only
      STATUS      current
      DESCRIPTION
        "The Qos priority assigned to a particular
         application-session (identified by destination IP
         and Port) on a BP."
      ::= { cabhPriorityQosBpDestEntry 5 }


   --===============================================================
   --
   --  PS Interface Attributes Table
   --
   --  The cabhPriorityQosPsIfAttribTable contains the number of
   --  media access priorities and number of queues associated with
   --  each LAN interface in the Residential Gateway.
   --
   --===============================================================

   cabhPriorityQosPsIfAttribTable   OBJECT-TYPE
           SYNTAX SEQUENCE OF CabhPriorityQosPsIfAttribEntry
           MAX-ACCESS   not-accessible
           STATUS    current
           DESCRIPTION
            "This table contains the number of media
             access priorities and number of queues associated
             with each LAN interface in the Residential Gateway."
            ::= { cabhPriorityQosPs 1  }

   cabhPriorityQosPsIfAttribEntry      OBJECT-TYPE
           SYNTAX    CabhPriorityQosPsIfAttribEntry
           MAX-ACCESS   not-accessible
           STATUS    current
           DESCRIPTION
             "Number of media access priorities and number
              of queues for each LAN interface in the
              Residential Gateway. This table applies only
              to interfaces through which data flows."
           INDEX { ifIndex }
           ::= { cabhPriorityQosPsIfAttribTable 1 }

   CabhPriorityQosPsIfAttribEntry ::= SEQUENCE {
      cabhPriorityQosPsIfAttribIfNumPriorities   Unsigned32,
           cabhPriorityQosPsIfAttribIfNumQueues   Unsigned32
   }

   cabhPriorityQosPsIfAttribIfNumPriorities OBJECT-TYPE
          SYNTAX     Unsigned32 (1..8)
          MAX-ACCESS read-only
          STATUS     current
          DESCRIPTION
           "The number of media access priorities supported
            by this LAN interface."
   ::= { cabhPriorityQosPsIfAttribEntry 1 }

   cabhPriorityQosPsIfAttribIfNumQueues OBJECT-TYPE
          SYNTAX     Unsigned32 (1..8)
          MAX-ACCESS read-only
          STATUS     current
          DESCRIPTION
           "The number of queues associated with this LAN
            interface."
   ::= { cabhPriorityQosPsIfAttribEntry 2 }


   -- Placeholder for notifications/traps.
   --

   cabhQosNotification         OBJECT IDENTIFIER  ::= { cabhQosMib 2 }
   cabhPriorityQosNotification OBJECT IDENTIFIER  ::= {
   cabhQosNotification 1 }



   --
   -- Conformance definitions
   --
   cabhQosConformance          OBJECT IDENTIFIER  ::= { cabhQosMib 3 }
   cabhPriorityQosConformance  OBJECT IDENTIFIER  ::= {
   cabhQosConformance 1 }
   cabhPriorityQosGroups       OBJECT IDENTIFIER  ::= {
   cabhPriorityQosConformance 1 }
   cabhPriorityQosCompliances  OBJECT IDENTIFIER  ::= {
   cabhPriorityQosConformance 2 }


   -- ==================

   -- compliance statements

   cabhPriorityQosCompliance MODULE-COMPLIANCE
       STATUS     current
       DESCRIPTION
         "The compliance statement for devices that implement
          CableHome 1.1 PriorityQos capability."

       MODULE   --cabhPriorityQosMib



   -- unconditionally mandatory groups

       MANDATORY-GROUPS {
               cabhPriorityQosGroup
       }

   ::= { cabhPriorityQosCompliances 1}


   cabhPriorityQosGroup OBJECT-GROUP
       OBJECTS {
       cabhPriorityQosMasterDefaultCHPriority,
       cabhPriorityQosMasterRowStatus,
       cabhPriorityQosSetToFactory,
       cabhPriorityQosBpIpAddrType,
       cabhPriorityQosBpIpAddr,
       cabhPriorityQosBpApplicationId,
       cabhPriorityQosBpDefaultCHPriority,
       cabhPriorityQosBpIndex,
       cabhPriorityQosBpDestIpAddrType,
       cabhPriorityQosBpDestIpAddr,
       cabhPriorityQosBpDestPort,
       cabhPriorityQosBpDestIpPortPriority,
       cabhPriorityQosPsIfAttribIfNumPriorities,
       cabhPriorityQosPsIfAttribIfNumQueues
       }
       STATUS    current
       DESCRIPTION
           "Group of objects for CableHome Application
            Priority MIB."
       ::= { cabhPriorityQosGroups 1 }

   END
