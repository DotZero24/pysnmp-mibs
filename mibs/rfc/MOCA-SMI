-- *****************************************************************
-- MOCA-SMI.my: MoCA Enterprise Structure of Management Information
--
-- Copyright (c) 2008 by Multimedia over Coax Alliance
-- All rights reserved.
--
-- *****************************************************************
--
MOCA-SMI DEFINITIONS ::= BEGIN
IMPORTS
	MODULE-IDENTITY,
	OBJECT-IDENTITY,
	enterprises
		FROM SNMPv2-SMI;

moca MODULE-IDENTITY
	LAST-UPDATED "200809220000Z" -- September 22, 2008 00:00 AM
	ORGANIZATION "Multimedia over Coax Alliance (MoCA) Technical Working Group."
	CONTACT-INFO	"www.mocalliance.org
					Postal: Multimedia over Coax Alliance
					2400 Camino Ramon
					Suite 375
					San Ramon, CA 94583
					USA
					Tel: +1 925 275-6606
					Email: help@mocalliance.org"

	DESCRIPTION
		"The Structure of Management Information (SMI) for
		Multimedia over Coax Alliance (MoCA) enterprise."

	REVISION "200809220000Z" -- September 22, 2008 00:00 AM
	DESCRIPTION
	"Initial version of this MIB module."
	::= { enterprises 31621 } -- assigned by IANA

mocaMIBs OBJECT-IDENTITY
	STATUS current
	DESCRIPTION
		"mocaMIBs is the root of the MoCAlliance assigned
		OID subtree for assignment to MIB modules describing
		managed objects implemented in MoCA devices that support
		MoCA MAC/PHY Specification."
	::= { moca 1 }
END
