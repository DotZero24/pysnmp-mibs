EAP-SYSTEMTOOLS-MIB DEFINITIONS ::= BEGIN

          IMPORTS
              OBJECT-TYPE
          	  	         FROM SNMPv2-SMI
              systemTools
          	  	         FROM TPLINK-MIB;

systemToolReboot OBJECT-TYPE
      SYNTAX  INTEGER{
              		notReboot(0), 			--normal state
              		reboot(1)
           }
              MAX-ACCESS  read-write
              STATUS  current
              DESCRIPTION
                      "this used to determine whether to reboot or not"
              ::= { systemTools 1 }
END
