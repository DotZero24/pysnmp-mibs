EAP-CLIENTTABLE-MIB    DEFINITIONS ::= BEGIN

IMPORTS
    MODULE-IDENTITY,OBJECT-TYPE
        FROM    SNMPv2-SMI
    clientStatis
        FROM    EAP-CLIENT-MIB;

    clientTable     OBJECT-TYPE
        SYNTAX       SEQUENCE OF ClientEntry
        MAX-ACCESS      not-accessible
        STATUS          current
        DESCRIPTION
            "This object indicates the wireless clients status associated with this EAP device."
        ::= { clientStatis 2 }
    clientEntry      OBJECT-TYPE
	SYNTAX	      ClientEntry
	MAX-ACCESS      not-accessible
	STATUS          current
        DESCRIPTION
	    "Clients Entry"
	INDEX{clientIndex}
	::= { clientTable 1 }
    ClientEntry ::=
	SEQUENCE
	{
	    clientIndex      INTEGER,
	    macAddress 	     OCTET STRING
	}
    clientIndex OBJECT-TYPE
	SYNTAX			INTEGER
	MAX-ACCESS		read-only
	STATUS			current
	DESCRIPTION
		"This object indicates the index of the client."
	::= { clientEntry 1 }
    macAddress OBJECT-TYPE
	SYNTAX 			OCTET STRING
	MAX-ACCESS		read-only
	STATUS			current
	DESCRIPTION
	"This object indicates the MAC Address of wireless clients."
	::= { clientEntry 2 }
END
