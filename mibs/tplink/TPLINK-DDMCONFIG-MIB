TPLINK-DDMCONFIG-MIB DEFINITIONS ::= BEGIN

         IMPORTS
            MODULE-IDENTITY, OBJECT-TYPE
          	  	        FROM SNMPv2-SMI
          	ifIndex
						FROM RFC1213-MIB
			DisplayString
						FROM SNMPv2-TC
			tplinkDdmManageMIBObjects
						FROM TPLINK-DDMMANAGE-MIB;

		   		ddmConfig MODULE-IDENTITY
				    LAST-UPDATED    "200908270000Z"
				    ORGANIZATION    "TPLINK"
				    CONTACT-INFO		"www.tplink.com"
				    DESCRIPTION			"The config of DDM."
				    REVISION        "200908270000Z"
				    DESCRIPTION			"Initial version of this MIB module."
				    ::= { tplinkDdmManageMIBObjects 1 }

				ddmConfigTable OBJECT-TYPE
					SYNTAX SEQUENCE OF DDMConfigEntry
					MAX-ACCESS	not-accessible
					STATUS			current
					DESCRIPTION
					"A table that is used to configure the action that will occur for specific ports when an exceeding alarm threshold or warning threshold event is encountered."
					::= { ddmConfig 1 }

				ddmConfigEntry OBJECT-TYPE
					SYNTAX			DDMConfigEntry
					MAX-ACCESS	not-accessible
					STATUS			current
					DESCRIPTION
					"A list of information for every port."
					INDEX { ifIndex }
					::= { ddmConfigTable 1 }

				DDMConfigEntry ::=
				SEQUENCE
				{
                    ddmConfigPort			DisplayString(SIZE(0..255)),
					ddmConfigStatus			INTEGER,
					ddmConfigShutdown		INTEGER,
					ddmConfigPortLAG		OCTET STRING(SIZE(0..30))
				}

				ddmConfigPort OBJECT-TYPE
					SYNTAX				DisplayString(SIZE(0..255))
					MAX-ACCESS			read-only
					STATUS				current
					DESCRIPTION
					"This object indicates the port number."
					::= { ddmConfigEntry 1 }

				ddmConfigStatus OBJECT-TYPE
					SYNTAX 				INTEGER { disable(0),enable(1) }
					MAX-ACCESS			read-write
					STATUS				current
					DESCRIPTION
					"This object indicates the DDM status of the port."
					::= { ddmConfigEntry 2 }

				ddmConfigShutdown OBJECT-TYPE
					SYNTAX				INTEGER { none(0),warning(1),alarm(2) }
					MAX-ACCESS			read-write
					STATUS				current
					DESCRIPTION
					"Specify whether to shutdown the port, when the operating parameter exceeds the Alarm or Warning threshold.
					Alarm - Shutdown the port when the configured alarm threshold range is exceeded.
					Warning - Shutdown the port when the configured warning threshold range is exceeded.
					None - The port will never shutdown regardless if the threshold ranges are exceeded or not. This is the default."
					::=	{ ddmConfigEntry 3 }

				ddmConfigPortLAG OBJECT-TYPE
					SYNTAX				OCTET STRING(SIZE(0..30))
					MAX-ACCESS			read-only
					STATUS				current
					DESCRIPTION
					"This object indicates the lag number of the port."
					::= { ddmConfigEntry 4 }

END
