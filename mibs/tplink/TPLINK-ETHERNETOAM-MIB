TPLINK-ETHERNETOAM-MIB DEFINITIONS ::= BEGIN
		IMPORTS
			OBJECT-TYPE,MODULE-IDENTITY
				FROM SNMPv2-SMI
			tplinkMgmt
				FROM TPLINK-MIB;

		tplinkEthernetOam MODULE-IDENTITY
		LAST-UPDATED	"201507061030Z"
		ORGANIZATION	"TPLINK"
		CONTACT-INFO	"www.tplink.com"
		DESCRIPTION		"Private MIB for Ethernet OAM."
		REVISION		"201507061030Z"
		DESCRIPTION		"Initial version of this MIB module."
		::= { tplinkMgmt 60 }

        tplinkEthernetOamMIBObjects			OBJECT IDENTIFIER ::= {tplinkEthernetOam 1}
		tplinkEthernetOamMIBNotifications	OBJECT IDENTIFIER ::= {tplinkEthernetOam 2}

		ethernetOamBasicConfig				OBJECT IDENTIFIER ::= {tplinkEthernetOamMIBObjects 1}
		ethernetOamLinkMonConfig			OBJECT IDENTIFIER ::= {tplinkEthernetOamMIBObjects 2}
		ethernetOamRfiConfig				OBJECT IDENTIFIER ::= {tplinkEthernetOamMIBObjects 3}
		ethernetOamRmtLbConfig				OBJECT IDENTIFIER ::= {tplinkEthernetOamMIBObjects 4}
		ethernetOamDiscoveryInfo			OBJECT IDENTIFIER ::= {tplinkEthernetOamMIBObjects 5}
		ethernetOamStatistics				OBJECT IDENTIFIER ::= {tplinkEthernetOamMIBObjects 6}
		ethernetOamEventLog					OBJECT IDENTIFIER ::= {tplinkEthernetOamMIBObjects 7}

END
