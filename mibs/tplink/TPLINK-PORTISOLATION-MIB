TPLINK-PORTISOLATION-MIB DEFINITIONS ::= BEGIN
		IMPORTS
			OBJECT-TYPE,MODULE-IDENTITY
			  	         	FROM SNMPv2-SMI
			tplinkMgmt
							FROM TPLINK-MIB
			ifIndex
							FROM RFC1213-MIB;

	tplinkPortIsolationMIB MODULE-IDENTITY
	    LAST-UPDATED    "201212130930Z"
	    ORGANIZATION    "TPLINK"
	    CONTACT-INFO	"www.tplink.com"
	    DESCRIPTION		"The config of the port isolation."
	    REVISION        "201212130930Z"
	    DESCRIPTION		"Initial version of this MIB module."
	    ::= { tplinkMgmt 13 }

		tplinkPortIsolationMIBObjects			OBJECT IDENTIFIER	::= { tplinkPortIsolationMIB 1 }
		tplinkPortIsolationMIBNotifications		OBJECT IDENTIFIER	::= { tplinkPortIsolationMIB 2 }

	   		portIsolationCtrlTable OBJECT-TYPE
              SYNTAX  SEQUENCE OF PORTISOLATIONCTRLENTRY
              MAX-ACCESS  not-accessible
              STATUS  current
              DESCRIPTION
                      "A list of port isolation."
              ::= { tplinkPortIsolationMIBObjects 1 }
         portIsolationCtrlEntry OBJECT-TYPE
              SYNTAX  PORTISOLATIONCTRLENTRY
              MAX-ACCESS  not-accessible
              STATUS  current
              DESCRIPTION
                      "The entry of the port isolation list ."
              INDEX   { ifIndex }
              ::= { portIsolationCtrlTable 1 }


        PORTISOLATIONCTRLENTRY ::=
              SEQUENCE {
                  portIsolationPortId
                      OCTET STRING,
                  portIsolationForList
                  		OCTET STRING,
                  portIsolationLagId
                  		OCTET STRING
              }

         portIsolationPortId  OBJECT-TYPE
			     SYNTAX  OCTET STRING (SIZE (0..16))
			      MAX-ACCESS  read-only
			      STATUS  current
			      DESCRIPTION
			              "The port id."
			      ::= { portIsolationCtrlEntry 1 }

			    portIsolationForList  OBJECT-TYPE
			     SYNTAX  OCTET STRING (SIZE (0..255))
			      MAX-ACCESS  read-write
			      STATUS  current
			      DESCRIPTION
			              "The forward portlist,such as 1/0/1-5,1/0/9-11,1/0/16."
			      ::= { portIsolationCtrlEntry 2 }

			    portIsolationLagId  OBJECT-TYPE
			     SYNTAX  OCTET STRING  (SIZE (0..10))
			      MAX-ACCESS  read-only
			      STATUS  current
			      DESCRIPTION
			              "The trunk id of the port."
			      ::= { portIsolationCtrlEntry 3 }

END
