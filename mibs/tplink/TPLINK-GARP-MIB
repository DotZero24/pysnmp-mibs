TPLINK-GARP-MIB	DEFINITIONS ::= BEGIN
    IMPORTS
	    TPRowStatus
  			FROM TPLINK-TC-MIB
		tplinkMgmt
			FROM TPLINK-MIB
        OBJECT-TYPE,IpAddress
          	FROM SNMPv2-SMI;

    MacAddress ::= OCTET STRING (SIZE (6))

	tplinkGarpMIB MODULE-IDENTITY
		LAST-UPDATED    "201411241442Z"
		ORGANIZATION    "TPLINK"
		CONTACT-INFO    "www.tplink.com"
		DESCRIPTION	    "Private MIB for gratuitous ARP configuration."
		REVISION        "201411241442Z"
		DESCRIPTION
				"Initial version of this MIB module."
		::= { tplinkMgmt 61 }

	tplinkGarpMIBObjects		OBJECT IDENTIFIER	::= { tplinkGarpMIB 1 }
	tplinkGarpNotifications	OBJECT IDENTIFIER	::= { tplinkGarpMIB 2 }

	--**************
	--Set gratuitous ARP
	--**************

    tpGarpConfig 		OBJECT IDENTIFIER ::= {tplinkGarpMIBObjects 1}

	tpGarpDupIpEnable OBJECT-TYPE
        SYNTAX  INTEGER{
			Disable(0),
			Enable(1)
		}
		MAX-ACCESS  read-write
		STATUS  current
		DESCRIPTION
		  	"Disable/Enable sending of gratuitous ARP when duplicate IP is detected"
		::=	{tpGarpConfig 1}

    tpGarpIntfUpEnable OBJECT-TYPE
        SYNTAX  INTEGER{
			Disable(0),
			Enable(1)
		}
		MAX-ACCESS  read-write
		STATUS  current
		DESCRIPTION
		  	"Disable/Enable sending of gratuitous ARP when interface status becom up"
		::=	{tpGarpConfig 2}

	tpGarpLearningEnable OBJECT-TYPE
        SYNTAX  INTEGER{
			Disable(0),
			Enable(1)
		}
		MAX-ACCESS  read-write
		STATUS  current
		DESCRIPTION
		  	"Disable/Enable learning of ARP entry based on the received gratuitous ARP packet"
		::=	{tpGarpConfig 3}

	tpGarpIntfConfig 		OBJECT IDENTIFIER ::= {tplinkGarpMIBObjects 2}

	tpGarpIntfConfigTable OBJECT-TYPE
		SYNTAX  SEQUENCE OF GARPENTRY
		MAX-ACCESS  not-accessible
		STATUS  current
		DESCRIPTION
			"Gratuitous Arp interface config table."
		::= { tpGarpIntfConfig 1 }

    tpGarpIntfConfigEntry OBJECT-TYPE
		SYNTAX  GARPENTRY
		MAX-ACCESS  not-accessible
		STATUS  current
		DESCRIPTION
			"An entry contains of the information of interface GARP configure."
		INDEX   { tpGarpInterface }
		::= { tpGarpIntfConfigTable 1 }

	GARPENTRY ::=
		SEQUENCE {
			tpGarpInterface
				OCTET STRING (SIZE (0..50)),
			tpGarpSendInterval
				INTEGER
		}

	tpGarpInterface OBJECT-TYPE
        SYNTAX  OCTET STRING (SIZE (0..50))
		MAX-ACCESS  read-only
		STATUS  current
		DESCRIPTION
			"Displays the interface."
		::= { tpGarpIntfConfigEntry 1 }

    tpGarpSendInterval OBJECT-TYPE
        SYNTAX  INTEGER(0..65535)
		MAX-ACCESS  read-write
		STATUS  current
		DESCRIPTION
		  	"Periodically send gratuitous ARP interval time in seconds. 0 means not send gratuitous"
		::=	{tpGarpIntfConfigEntry 2}

	tpGarpIpDuplicate NOTIFICATION-TYPE
		OBJECTS
		{
			tpGarpInterface
		}
		STATUS          current
		DESCRIPTION
		"A tpGarpIpDuplicate notification is sent when duplicate IP is detected."
		::= { tplinkGarpNotifications 1 }

END
