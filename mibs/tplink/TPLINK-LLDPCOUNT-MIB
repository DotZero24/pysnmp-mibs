TPLINK-LLDPCOUNT-MIB DEFINITIONS ::= BEGIN

       IMPORTS
            MODULE-IDENTITY,OBJECT-TYPE,IpAddress
          	  	    FROM SNMPv2-SMI
            tplinkLldpMIBObjects,tplinkLldpMIBNotifications
					FROM TPLINK-LLDP-MIB
			ifIndex
					FROM RFC1213-MIB;

          	lldpCount OBJECT IDENTIFIER ::= {tplinkLldpMIBObjects 3}

			MacAddress ::= OCTET STRING (SIZE (6))

			 lldpGlobalCount	  	OBJECT IDENTIFIER ::= {lldpCount 1}

				  lldpGlobalCountUpdateTime OBJECT-TYPE
         			SYNTAX  OCTET STRING (SIZE (0..20))
              MAX-ACCESS  read-only
              STATUS  current
              DESCRIPTION
                      "The time how long the information has updated."
              ::= { lldpGlobalCount 1 }

          lldpGlobalCountNeighborInserted OBJECT-TYPE
         			SYNTAX  INTEGER
              MAX-ACCESS  read-only
              STATUS  current
              DESCRIPTION
                      "Display the newest number of the neighbor."
              ::= { lldpGlobalCount 2 }

           lldpGlobalCountNeighborDeleted OBJECT-TYPE
         			SYNTAX  INTEGER
              MAX-ACCESS  read-only
              STATUS  current
              DESCRIPTION
                      "Display how many neighbors the local device has deleted."
              ::= { lldpGlobalCount 3 }

          lldpGlobalCountNeighborDroped OBJECT-TYPE
         			SYNTAX  INTEGER
              MAX-ACCESS  read-only
              STATUS  current
              DESCRIPTION
                      "Display how many neighbors the local device has discarded."
              ::= { lldpGlobalCount 4 }

          lldpGlobalCountNeighborAged OBJECT-TYPE
         			SYNTAX  INTEGER
              MAX-ACCESS  read-only
              STATUS  current
              DESCRIPTION
                      "Display how many neighbors was time out in the local device."
              ::= { lldpGlobalCount 5 }

					lldpCountNeighborInfoTable OBJECT-TYPE
              SYNTAX  SEQUENCE OF LLDPCOUNTNEIGHBORINFOENTRY
              MAX-ACCESS  not-accessible
              STATUS  current
              DESCRIPTION
                      "The statistic information entries of the neighbor device."
              ::= { lldpCount 2 }

          lldpCountNeighborInfoEntry OBJECT-TYPE
              SYNTAX  LLDPCOUNTNEIGHBORINFOENTRY
              MAX-ACCESS  not-accessible
              STATUS  current
              DESCRIPTION
                      "An entry contains of the information of the neighboe device."
              INDEX   { ifIndex }
              ::= { lldpCountNeighborInfoTable 1 }

          LLDPCOUNTNEIGHBORINFOENTRY ::=
              SEQUENCE {
              		lldpCountNeighborPortId
              				OCTET STRING,
                  lldpNeighborFramesOut
              				INTEGER,
              	  lldpNeighborFramesIn
              				INTEGER,
              	  lldpNeighborFramesDiscarded
              				INTEGER,
              	  lldpNeighborFramesInErrors
              				INTEGER,
              	  lldpNeighborAgeOuts
              				INTEGER,
              	  lldpNeighborTlvDiscarded
              				INTEGER,
              	  lldpNeighborTlvUnrecognized
              				INTEGER
              	}


          lldpCountNeighborPortId OBJECT-TYPE
            	SYNTAX  OCTET STRING (SIZE (0..255))
              MAX-ACCESS  read-only
              STATUS  current
              DESCRIPTION
                      "Displays the port ID of the switch."
              ::= { lldpCountNeighborInfoEntry 1 }

          lldpNeighborFramesOut OBJECT-TYPE
            	SYNTAX  INTEGER
              MAX-ACCESS  read-only
              STATUS  current
              DESCRIPTION
                      "Displays the number of the frames sent by this port."
              ::= { lldpCountNeighborInfoEntry 2 }

          lldpNeighborFramesIn OBJECT-TYPE
            	SYNTAX  INTEGER
              MAX-ACCESS  read-only
              STATUS  current
              DESCRIPTION
                      "Displays the number of the frames received by this port."
              ::= { lldpCountNeighborInfoEntry 3 }

          lldpNeighborFramesDiscarded OBJECT-TYPE
            	SYNTAX  INTEGER
              MAX-ACCESS  read-only
              STATUS  current
              DESCRIPTION
                      "Displays the number of the frams discarded by this port."
              ::= { lldpCountNeighborInfoEntry 4 }

          lldpNeighborFramesInErrors OBJECT-TYPE
            	SYNTAX  INTEGER
              MAX-ACCESS  read-only
              STATUS  current
              DESCRIPTION
                      "Displays the number of the error frames recived by this port."
              ::= { lldpCountNeighborInfoEntry 5 }

          lldpNeighborAgeOuts OBJECT-TYPE
            	SYNTAX  INTEGER
              MAX-ACCESS  read-only
              STATUS  current
              DESCRIPTION
                      "Displays the number of the time out neighbor which connected to this port."
              ::= { lldpCountNeighborInfoEntry 6 }

          lldpNeighborTlvDiscarded OBJECT-TYPE
            	SYNTAX  INTEGER
              MAX-ACCESS  read-only
              STATUS  current
              DESCRIPTION
                      "Displays the number of discarded TLV when this port received LLDPDU."
              ::= { lldpCountNeighborInfoEntry 7 }

          lldpNeighborTlvUnrecognized OBJECT-TYPE
            	SYNTAX  INTEGER
              MAX-ACCESS  read-only
              STATUS  current
              DESCRIPTION
                      "Displays the number of the unrecognized TLV when this port received LLDPDU."
              ::= { lldpCountNeighborInfoEntry 8 }

			lldpNeighborChange NOTIFICATION-TYPE
				OBJECTS
				{
					lldpGlobalCountNeighborInserted,
					lldpGlobalCountNeighborDeleted,
					lldpGlobalCountNeighborDroped,
					lldpGlobalCountNeighborAged
				}
				STATUS          current
				DESCRIPTION
					""
			::= { tplinkLldpMIBNotifications 1}
	 END
