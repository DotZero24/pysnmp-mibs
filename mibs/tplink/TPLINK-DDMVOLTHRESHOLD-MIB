TPLINK-DDMVOLTHRESHOLD-MIB DEFINITIONS ::= BEGIN

         IMPORTS
            MODULE-IDENTITY, OBJECT-TYPE
          	  	        FROM SNMPv2-SMI
          	ifIndex
						FROM RFC1213-MIB
			DisplayString
						FROM SNMPv2-TC
			tplinkDdmManageMIBObjects
						FROM TPLINK-DDMMANAGE-MIB;

		   		ddmVolThreshold MODULE-IDENTITY
				    LAST-UPDATED    "200908270000Z"
				    ORGANIZATION    "TPLINK"
				    CONTACT-INFO		"www.tplink.com"
				    DESCRIPTION			"The config of DDM voltage threshold."
				    REVISION        "200908270000Z"
				    DESCRIPTION			"Initial version of this MIB module."
				    ::= { tplinkDdmManageMIBObjects 3 }

				ddmVolThresholdTable OBJECT-TYPE
					SYNTAX SEQUENCE OF DDMVolThresholdEntry
					MAX-ACCESS	not-accessible
					STATUS			current
					DESCRIPTION
					"A table that is used to configure the DDM Voltage Threshold for specific ports on the Switch."
					::= { ddmVolThreshold 1 }

				ddmVolThresholdEntry OBJECT-TYPE
					SYNTAX			DDMVolThresholdEntry
					MAX-ACCESS	not-accessible
					STATUS			current
					DESCRIPTION
					"A list of information for every port."
					INDEX { ifIndex }
					::= { ddmVolThresholdTable 1 }

				DDMVolThresholdEntry ::=
				SEQUENCE
				{
                    ddmVolThresholdPort				DisplayString(SIZE(0..255)),
					ddmVolThresholdHighAlarm		OCTET STRING(SIZE(0..30)),
					ddmVolThresholdLowAlarm			OCTET STRING(SIZE(0..30)),
					ddmVolThresholdHighWarn			OCTET STRING(SIZE(0..30)),
					ddmVolThresholdLowWarn			OCTET STRING(SIZE(0..30)),
					ddmVolThresholdPortLAG			OCTET STRING(SIZE(0..30))
				}

				ddmVolThresholdPort OBJECT-TYPE
					SYNTAX				DisplayString(SIZE(0..255))
					MAX-ACCESS			read-only
					STATUS				current
					DESCRIPTION
					"This object indicates the port number."
					::= { ddmVolThresholdEntry 1 }

				ddmVolThresholdHighAlarm OBJECT-TYPE
					SYNTAX 				OCTET STRING(SIZE(0..30))
					MAX-ACCESS			read-write
					STATUS				current
					DESCRIPTION
					"This object indicates the highest threshold for the alarm."
					::= { ddmVolThresholdEntry 2 }

				ddmVolThresholdLowAlarm OBJECT-TYPE
					SYNTAX				OCTET STRING(SIZE(0..30))
					MAX-ACCESS			read-write
					STATUS				current
					DESCRIPTION
					"This object indicates the lowest threshold for the alarm."
					::=	{ ddmVolThresholdEntry 3 }

				ddmVolThresholdHighWarn OBJECT-TYPE
					SYNTAX 				OCTET STRING(SIZE(0..30))
					MAX-ACCESS			read-write
					STATUS				current
					DESCRIPTION
					"This object indicates the highest threshold for the warning."
					::= { ddmVolThresholdEntry 4 }

				ddmVolThresholdLowWarn OBJECT-TYPE
					SYNTAX				OCTET STRING(SIZE(0..30))
					MAX-ACCESS			read-write
					STATUS				current
					DESCRIPTION
					"This object indicates the lowest threshold for the warning."
					::=	{ ddmVolThresholdEntry 5 }

				ddmVolThresholdPortLAG OBJECT-TYPE
					SYNTAX				OCTET STRING(SIZE(0..30))
					MAX-ACCESS			read-only
					STATUS				current
					DESCRIPTION
					"This object indicates the lag number of the port."
					::= { ddmVolThresholdEntry 6 }

END
