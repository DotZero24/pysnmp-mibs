TPLINK-ETHERNETOAMLINKMONCFG-MIB DEFINITIONS ::= BEGIN
		IMPORTS
			OBJECT-TYPE,Unsigned32		FROM SNMPv2-SMI
			ethernetOamLinkMonConfig	FROM TPLINK-ETHERNETOAM-MIB
			DisplayString
							FROM SNMPv2-TC
			ifIndex
							FROM RFC1213-MIB;

		ethernetOamLinkMonCfgTable OBJECT-TYPE
			SYNTAX SEQUENCE OF EthernetOamLinkMonCfgEntry
			MAX-ACCESS	not-accessible
			STATUS	current
			DESCRIPTION
			"A table that contains link monitoring configuration of each port.
			Through link monitoring, you can detect and find faults in various environments at the data link layer.
			Link monitoring uses event notification PDUs. When a link event occurs, the local link notifies the OAM entity of the event."
			::= {ethernetOamLinkMonConfig 1}

		ethernetOamLinkMonCfgEntry OBJECT-TYPE
			SYNTAX EthernetOamLinkMonCfgEntry
			MAX-ACCESS	not-accessible
			STATUS	current
			DESCRIPTION
			"An entry that contains the link monitoring configuration of each port."
			INDEX {ifIndex, ethernetOamLinkMonCfgEvent}
			::= {ethernetOamLinkMonCfgTable 1}

		EthernetOamLinkMonCfgEntry ::=
		SEQUENCE
		{
			ethernetOamLinkMonCfgPort		DisplayString,
			ethernetOamLinkMonCfgEvent		INTEGER,
			ethernetOamLinkMonCfgThreshold	Unsigned32,
			ethernetOamLinkMonCfgWindow		Unsigned32,
			ethernetOamLinkMonCfgNotify		INTEGER,
			ethernetOamLinkMonCfgLAG		OCTET STRING(SIZE(0..10))
		}

		ethernetOamLinkMonCfgPort OBJECT-TYPE
			SYNTAX DisplayString
			MAX-ACCESS	read-only
			STATUS	current
			DESCRIPTION
			"Displays the port number."
			::= {ethernetOamLinkMonCfgEntry 1}

		ethernetOamLinkMonCfgEvent OBJECT-TYPE
			SYNTAX INTEGER {symbol-period(1), frame(2), frame-period(3), frame-seconds(4)}
			MAX-ACCESS	read-only
			STATUS	current
			DESCRIPTION
			"Select various types of link monitoring."
			::= {ethernetOamLinkMonCfgEntry 2}

		ethernetOamLinkMonCfgThreshold OBJECT-TYPE
			SYNTAX Unsigned32
			MAX-ACCESS	read-write
			STATUS	current
			DESCRIPTION
			"Enter the number of errors that is required to be equal to or greater than in order for the event to be generated."
			::= {ethernetOamLinkMonCfgEntry 3}

		ethernetOamLinkMonCfgWindow OBJECT-TYPE
			SYNTAX Unsigned32
			MAX-ACCESS	read-write
			STATUS	current
			DESCRIPTION
			"Enter the period of the event. The unit is 100ms for symbol-period, frame, frame-seconds link event and 1 frame for frame-period link event."
			::= {ethernetOamLinkMonCfgEntry 4}

		ethernetOamLinkMonCfgNotify OBJECT-TYPE
			SYNTAX INTEGER {disable(0),enable(1)}
			MAX-ACCESS	read-write
			STATUS	current
			DESCRIPTION
			"Select to enable or disable the event notification."
			::= {ethernetOamLinkMonCfgEntry 5}

		ethernetOamLinkMonCfgLAG OBJECT-TYPE
			SYNTAX OCTET STRING(SIZE(0..10))
			MAX-ACCESS	read-only
			STATUS	current
			DESCRIPTION
			"Displays the LAG number of the port."
			::= {ethernetOamLinkMonCfgEntry 6}

END
