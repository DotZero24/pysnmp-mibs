TPLINK-CLUSTER-MIB DEFINITIONS ::= BEGIN

         IMPORTS
            MODULE-IDENTITY
          	  	         	FROM SNMPv2-SMI
            tplinkClusterMIBObjects
          	  	          FROM TPLINK-CLUSTERTREE-MIB;

	     tplinkClusterMIB MODULE-IDENTITY
		    LAST-UPDATED    "200908270000Z"
		    ORGANIZATION    "TPLINK"
		    CONTACT-INFO		"www.tplink.com.cn"
	   	 	DESCRIPTION			"Cluster Management function enables a network administer to
									   	 	manage the scattered devices in the network via a management
									   	 	device. After a commander switch is configured, management
									   	 	and maintenance operations intended for the member devices
									   	 	in a cluster is implemented by the commander device. "
		    REVISION        "200908270000Z"
		    DESCRIPTION			"Initial version of this MIB module."
	    	::= { tplinkClusterMIBObjects 1 }

	    ndpManage		OBJECT IDENTIFIER 	::= {tplinkClusterMIB 1}
	    ntdpManage 	OBJECT IDENTIFIER 	::= {tplinkClusterMIB 2}
	    clusterManage	OBJECT IDENTIFIER	::= {tplinkClusterMIB 3}
END
