TPLINK-IPMROUTE-MIB DEFINITIONS ::= BEGIN

	IMPORTS
		MODULE-IDENTITY, OBJECT-TYPE,Integer32,
		IpAddress, TimeTicks
			FROM SNMPv2-SMI
		tplinkMgmt
			FROM TPLINK-MIB;

	tplinkIpMrouteMIB MODULE-IDENTITY
		LAST-UPDATED    "201212130930Z"
		ORGANIZATION    "TPLINK"
		CONTACT-INFO    "www.tplink.com"
		DESCRIPTION	    "Private MIB for PIM configuration."
		REVISION        "201212130930Z"
		DESCRIPTION
				"Initial version of this MIB module."
		::= { tplinkMgmt 78 }


	tplinkIpMrouteMIBObjects      OBJECT IDENTIFIER ::= { tplinkIpMrouteMIB 1 }
	tplinkIpMrouteNotifications   OBJECT IDENTIFIER ::= { tplinkIpMrouteMIB 2 }
	tpIpMRoute                    OBJECT IDENTIFIER ::= { tplinkIpMrouteMIBObjects 1 }

-- the IP Multicast Routing MIB-Group

	tpIpMRouteEnable OBJECT-TYPE
		SYNTAX     INTEGER { enabled(1), disabled(2) }
		MAX-ACCESS read-write
		STATUS     current
		DESCRIPTION
				"Select enable or disable to set the status of Multicast
				Forwarding in the router. The default is disable."
		::= { tpIpMRoute 1 }

	tpIpMRouteSGTable OBJECT-TYPE
		SYNTAX     SEQUENCE OF TpIpMRouteSGEntry
		MAX-ACCESS not-accessible
		STATUS     current
		DESCRIPTION
				"The (conceptual) table containing multicast routing
				information for IP datagrams sent by particular sources to
				the IP multicast groups known to this router."
		::= { tpIpMRoute 2 }

	tpIpMRouteSGEntry OBJECT-TYPE
		SYNTAX     TpIpMRouteSGEntry
		MAX-ACCESS not-accessible
		STATUS     current
		DESCRIPTION
				"An entry (conceptual row) containing the multicast routing
				information for IP datagrams from a particular source and
				addressed to a particular IP multicast group address."
		INDEX      { tpIpMRouteSGGroup,
					 tpIpMRouteSGSource}
		::= { tpIpMRouteSGTable 1 }

	TpIpMRouteSGEntry ::= SEQUENCE {
		tpIpMRouteSGGroup		                IpAddress,
		tpIpMRouteSGSource		            IpAddress,
		tpIpMRouteSGIncomingInterface		  OCTET STRING (SIZE (0..32)),
		tpIpMRouteSGOutgoingInterface		  OCTET STRING (SIZE (0..1024)),
		tpIpMRouteSGRpfNeighbor               IpAddress,
		tpIpMRouteSGUpTime		            TimeTicks,
		tpIpMRouteSGExpiryTime		        TimeTicks,
		tpIpMRouteSGProtocol		            INTEGER,
		tpIpMRouteSGFlags		                INTEGER
	}

	tpIpMRouteSGGroup OBJECT-TYPE
		SYNTAX     IpAddress
		MAX-ACCESS read-only
		STATUS     current
		DESCRIPTION
				"The destination group IP address."
		::= { tpIpMRouteSGEntry 1 }

	tpIpMRouteSGSource OBJECT-TYPE
		SYNTAX     IpAddress
		MAX-ACCESS read-only
		STATUS     current
		DESCRIPTION
				"The IP address of the multicast packet source to be combined with
				the Group IP to fully identify a single route whose Mroute table
				entry."
		::= { tpIpMRouteSGEntry 2 }

	tpIpMRouteSGIncomingInterface OBJECT-TYPE
		SYNTAX     OCTET STRING (SIZE (0..32))
		MAX-ACCESS read-only
		STATUS     current
		DESCRIPTION
				"The incoming interface on which multicast packets for this source
				/group arrive."
		::= { tpIpMRouteSGEntry 3 }

	tpIpMRouteSGOutgoingInterface OBJECT-TYPE
		SYNTAX     OCTET STRING (SIZE (0..1024))
		MAX-ACCESS read-only
		STATUS     current
		DESCRIPTION
				"The list of outgoing interfaces on which multicast packets for this
				source/group are forwarded."
		::= { tpIpMRouteSGEntry 4 }

	tpIpMRouteSGRpfNeighbor OBJECT-TYPE
		SYNTAX     IpAddress
		MAX-ACCESS read-only
		STATUS     current
		DESCRIPTION
				"The address of the upstream neighbor (e.g., RPF neighbor)
			from which IP datagrams from these sources to this multicast
			address are received, or 0.0.0.0 if the upstream neighbor is
			unknown (e.g., in CBT)."
		::= { tpIpMRouteSGEntry 5 }

	tpIpMRouteSGUpTime OBJECT-TYPE
		SYNTAX     TimeTicks
		MAX-ACCESS read-only
		STATUS     current
		DESCRIPTION
				"The time in seconds since the entry was created."
		::= { tpIpMRouteSGEntry 6 }

	tpIpMRouteSGExpiryTime OBJECT-TYPE
		SYNTAX     TimeTicks
		MAX-ACCESS read-only
		STATUS     current
		DESCRIPTION
				"The time in seconds before this entry will age out and be
				removed from the table."
		::= { tpIpMRouteSGEntry 7 }

	tpIpMRouteSGProtocol OBJECT-TYPE
		SYNTAX  INTEGER {
					pimDenseMode(1),
					pimSparseMode(2)
				}
		MAX-ACCESS read-only
		STATUS     current
		DESCRIPTION
				"The multicast routing protocol which created this entry. The
				possibilities are: PIM-DM,PIM-SM."
		::= { tpIpMRouteSGEntry 8 }

	tpIpMRouteSGFlags OBJECT-TYPE
		SYNTAX  INTEGER {
					spt(1),		             -- shortest path tree
					rpt(2)		             -- shared tree
				}
		MAX-ACCESS read-only
		STATUS     current
		DESCRIPTION
				"The value displayed in this field is valid if the multicast routing
				protocol running is PIMSM. The possible values are RPT or SPT. For
				other protocols an "------" is displayed."
		::= { tpIpMRouteSGEntry 9 }



		tpIpMRouteStarGTable OBJECT-TYPE
		SYNTAX     SEQUENCE OF TpIpMRouteStarGEntry
		MAX-ACCESS not-accessible
		STATUS     current
		DESCRIPTION
				"The (conceptual) table containing multicast routing
				information for IP datagrams sent by particular sources to
				the IP multicast groups known to this router."
		::= { tpIpMRoute 3 }

	tpIpMRouteStarGEntry OBJECT-TYPE
		SYNTAX     TpIpMRouteStarGEntry
		MAX-ACCESS not-accessible
		STATUS     current
		DESCRIPTION
				"An entry (conceptual row) containing the multicast routing
				information for IP datagrams from a particular source and
				addressed to a particular IP multicast group address."
		INDEX      { tpIpMRouteStarGGroup}
		::= { tpIpMRouteStarGTable 1 }

	TpIpMRouteStarGEntry ::= SEQUENCE {
		tpIpMRouteStarGGroup		                IpAddress,
		tpIpMRouteStarGSource		            IpAddress,
		tpIpMRouteStarGIncomingInterface		     OCTET STRING (SIZE (0..32)),
		tpIpMRouteStarGOutgoingInterface		     OCTET STRING (SIZE (0..1024)),
		tpIpMRouteStarGRpfNeighbor               IpAddress,
		tpIpMRouteStarGUpTime		            TimeTicks,
		tpIpMRouteStarGExpiryTime		        TimeTicks,
		tpIpMRouteStarGProtocol		            INTEGER,
		tpIpMRouteStarGFlags		                INTEGER
	}

	tpIpMRouteStarGGroup OBJECT-TYPE
		SYNTAX     IpAddress
		MAX-ACCESS read-only
		STATUS     current
		DESCRIPTION
				"The destination group IP address."
		::= { tpIpMRouteStarGEntry 1 }

	tpIpMRouteStarGSource OBJECT-TYPE
		SYNTAX     IpAddress
		MAX-ACCESS read-only
		STATUS     current
		DESCRIPTION
				"The IP address of the multicast packet source to be combined with
				the Group IP to fully identify a single route whose Mroute table
				entry."
		::= { tpIpMRouteStarGEntry 2 }

	tpIpMRouteStarGIncomingInterface OBJECT-TYPE
		SYNTAX     OCTET STRING (SIZE (0..32))
		MAX-ACCESS read-only
		STATUS     current
		DESCRIPTION
				"The incoming interface on which multicast packets for this source
				/group arrive."
		::= { tpIpMRouteStarGEntry 3 }

	tpIpMRouteStarGOutgoingInterface OBJECT-TYPE
		SYNTAX     OCTET STRING (SIZE (0..1024))
		MAX-ACCESS read-only
		STATUS     current
		DESCRIPTION
				"The list of outgoing interfaces on which multicast packets for this
				source/group are forwarded."
		::= { tpIpMRouteStarGEntry 4 }

	tpIpMRouteStarGRpfNeighbor OBJECT-TYPE
		SYNTAX     IpAddress
		MAX-ACCESS read-only
		STATUS     current
		DESCRIPTION
				"The address of the upstream neighbor (e.g., RPF neighbor)
			from which IP datagrams from these sources to this multicast
			address are received, or 0.0.0.0 if the upstream neighbor is
			unknown (e.g., in CBT)."
		::= { tpIpMRouteStarGEntry 5 }

	tpIpMRouteStarGUpTime OBJECT-TYPE
		SYNTAX     TimeTicks
		MAX-ACCESS read-only
		STATUS     current
		DESCRIPTION
				"The time in seconds since the entry was created."
		::= { tpIpMRouteStarGEntry 6 }

	tpIpMRouteStarGExpiryTime OBJECT-TYPE
		SYNTAX     TimeTicks
		MAX-ACCESS read-only
		STATUS     current
		DESCRIPTION
				"The time in seconds before this entry will age out and be
				removed from the table."
		::= { tpIpMRouteStarGEntry 7 }

	tpIpMRouteStarGProtocol OBJECT-TYPE
		SYNTAX  INTEGER {
					pimDenseMode(1),
					pimSparseMode(2)
				}
		MAX-ACCESS read-only
		STATUS     current
		DESCRIPTION
				"The multicast routing protocol which created this entry. The
				possibilities are: PIM-DM,PIM-SM."
		::= { tpIpMRouteStarGEntry 8 }

	tpIpMRouteStarGFlags OBJECT-TYPE
		SYNTAX  INTEGER {
					spt(1),		             -- shortest path tree
					rpt(2)		             -- shared tree
				}
		MAX-ACCESS read-only
		STATUS     current
		DESCRIPTION
				"The value displayed in this field is valid if the multicast routing
				protocol running is PIMSM. The possible values are RPT or SPT. For
				other protocols an "------" is displayed."
		::= { tpIpMRouteStarGEntry 9 }


--  The IP Multicast Routing Next Hop Table

--
--  The Multicast Routing Interface Table
--

--
--  The IP Multicast Scoped Boundary Table
--

-- conformance information

-- compliance statements

-- units of conformance

END
