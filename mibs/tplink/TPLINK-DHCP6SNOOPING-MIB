TPLINK-DHCP6SNOOPING-MIB DEFINITIONS ::= BEGIN

         IMPORTS
            MODULE-IDENTITY, OBJECT-TYPE
          	  	        FROM SNMPv2-SMI
          	ifIndex
						FROM RFC1213-MIB
            tplinkMgmt
						FROM TPLINK-MIB;

			tplinkDhcp6SnoopingMIB MODULE-IDENTITY
				LAST-UPDATED    "201212171014Z"
				ORGANIZATION    "TPLINK"
				CONTACT-INFO    "www.tplink.com"
				DESCRIPTION	    "Private MIB for DHCPv6 Snooping configuration."
				REVISION        "201212171014Z"
				DESCRIPTION
				"Initial version of this MIB module."
			::= { tplinkMgmt 91 }

			tplinkDhcp6SnoopingMIBObjects		OBJECT IDENTIFIER	::= { tplinkDhcp6SnoopingMIB 1 }
			tplinkDhcp6SnoopingNotifications		OBJECT IDENTIFIER	::= { tplinkDhcp6SnoopingMIB 2 }

  			dhcp6SnoopingGlobalConfig		OBJECT IDENTIFIER	::= { tplinkDhcp6SnoopingMIBObjects 1 }
            dhcp6SnoopingPortConfig     		OBJECT IDENTIFIER	::= { tplinkDhcp6SnoopingMIBObjects 3 }

				dhcp6SnoopingEnable OBJECT-TYPE
	          		SYNTAX  INTEGER{
	      				disable(0),
	      				enable(1)
	      			}
	            MAX-ACCESS  read-write
	            STATUS  current
	            DESCRIPTION
	                    "0. disable
	                     1. enable
	                     Enable or disable the DHCPv6 Snooping function globally."
	            ::= { dhcp6SnoopingGlobalConfig 1 }

				dhcp6SnoopingVlanConfigTable OBJECT-TYPE
					SYNTAX  	SEQUENCE OF Dhcp6SnoopingVlanConfigTable
					MAX-ACCESS  not-accessible
					STATUS  	current
					DESCRIPTION
							"Here you can view and modify the DHCPv6 Snooping VLAN config table."
				::= { dhcp6SnoopingGlobalConfig 2 }

				dhcp6SnoopingVlanConfigEntry OBJECT-TYPE
					SYNTAX  	Dhcp6SnoopingVlanConfigTable
					MAX-ACCESS  not-accessible
					STATUS  	current
					DESCRIPTION
							"An entry contains of the DHCPv6 Snooping function enable status information of a VLAN."
					INDEX   { dhcp6SnoopingVlanId }
				::= { dhcp6SnoopingVlanConfigTable 1 }

				Dhcp6SnoopingVlanConfigTable ::=
					SEQUENCE {
						dhcp6SnoopingVlanId
								INTEGER(1..4094),
						dhcp6SnoopingVlanStatus
								INTEGER
					}

				dhcp6SnoopingVlanId OBJECT-TYPE
					SYNTAX 	 	INTEGER(1..4094)
					MAX-ACCESS  read-only
					STATUS  	current
					DESCRIPTION
							"Enter the ID number of VLAN,1-4094."
				::= { dhcp6SnoopingVlanConfigEntry 1 }

        		dhcp6SnoopingVlanStatus OBJECT-TYPE
	          		SYNTAX  INTEGER{
	      				disable(0),
	      				enable(1)
	      			}
	            	MAX-ACCESS  read-write
	            	STATUS  current
	            	DESCRIPTION
	                    "0. disable
	                     1. enable
	                     Enable or disable DHCPv6 Snooping function in specified VLAN. "
	            ::= { dhcp6SnoopingVlanConfigEntry 2 }
       -- the dhcp snooping	port config

       			dhcp6SnoopingPortConfigTable OBJECT-TYPE
          			SYNTAX  SEQUENCE OF Dhcp6SnoopingPortConfigEntry
          			MAX-ACCESS  not-accessible
          			STATUS  current
          			DESCRIPTION
                  		"A list of DHCPv6 Snooping port config entries.
                   		Here you can configure the port parameters for the DHCPv6 Snooping."
          		::= { dhcp6SnoopingPortConfig 1 }

      			dhcp6SnoopingPortConfigEntry OBJECT-TYPE
          			SYNTAX  Dhcp6SnoopingPortConfigEntry
          			MAX-ACCESS  not-accessible
          			STATUS  current
          			DESCRIPTION
                  		"An entry contains of the information of DHCPv6 Snooping port config."
          			INDEX   {ifIndex}
          		::= { dhcp6SnoopingPortConfigTable 1 }

      			Dhcp6SnoopingPortConfigEntry ::=
          			SEQUENCE {
          					dhcp6SnoopingPort
          						    OCTET STRING (SIZE (0..255)),
							dhcp6SnoopingPortConfigMaxEntry
									INTEGER,
							dhcp6SnoopingPortConfigPortLag
									OCTET STRING
          			}

                dhcp6SnoopingPort OBJECT-TYPE
					SYNTAX  	OCTET STRING (SIZE (0..255))
					MAX-ACCESS  read-only
					STATUS  	current
					DESCRIPTION
						"Display port number"
				::= { dhcp6SnoopingPortConfigEntry 1 }

      			dhcp6SnoopingPortConfigMaxEntry OBJECT-TYPE
          			SYNTAX  INTEGER
          			MAX-ACCESS  read-write
          			STATUS  current
          			DESCRIPTION
                  		"Set the maxinum entry of the interface."
          		::= { dhcp6SnoopingPortConfigEntry 2 }

      			dhcp6SnoopingPortConfigPortLag OBJECT-TYPE
            		SYNTAX  OCTET STRING (SIZE (1..255))
            		MAX-ACCESS  read-only
            		STATUS  current
            		DESCRIPTION
                    	"The LAG to which the port belongs to."
            	::= { dhcp6SnoopingPortConfigEntry 3 }

END
