TPLINK-ETHERNETOAMEVENTLOG-MIB DEFINITIONS ::= BEGIN
		IMPORTS
			OBJECT-TYPE,Counter64	FROM SNMPv2-SMI
			Counter					FROM RFC1155-SMI
			ethernetOamEventLog		FROM TPLINK-ETHERNETOAM-MIB
			DisplayString
							FROM SNMPv2-TC
			ifIndex
							FROM RFC1213-MIB;

		ethernetOamEventLogStatTable OBJECT-TYPE
			SYNTAX SEQUENCE OF EthernetOamEventLogStatEntry
			MAX-ACCESS	not-accessible
			STATUS	current
			DESCRIPTION
			"A table that contains the Ethernet OAM event log statistics of each port."
			::= {ethernetOamEventLog 1}

		ethernetOamEventLogStatEntry OBJECT-TYPE
			SYNTAX EthernetOamEventLogStatEntry
			MAX-ACCESS	not-accessible
			STATUS	current
			DESCRIPTION
			"An entry that contains the Ethernet OAM event log statistics of each port."
			INDEX {ifIndex}
			::= {ethernetOamEventLogStatTable 1}

		EthernetOamEventLogStatEntry ::=
		SEQUENCE
		{
			ethernetOamEventLogStatPort					DisplayString,
			ethernetOamEventLogStatLocalSymbolPeriod	Counter,
			ethernetOamEventLogStatRemoteSymbolPeriod	Counter,
			ethernetOamEventLogStatLocalFrame			Counter,
			ethernetOamEventLogStatRemoteFrame			Counter,
            ethernetOamEventLogStatLocalFramePeriod		Counter,
			ethernetOamEventLogStatRemoteFramePeriod	Counter,
			ethernetOamEventLogStatLocalFrameSeconds	Counter,
			ethernetOamEventLogStatRemoteFrameSeconds	Counter,
			ethernetOamEventLogStatLocalDyingGasp		Counter,
			ethernetOamEventLogStatRemoteDyingGasp		Counter,
			ethernetOamEventLogStatLocalCriticalEvent	Counter,
			ethernetOamEventLogStatRemoteCriticalEvent	Counter
		}

		ethernetOamEventLogStatPort OBJECT-TYPE
			SYNTAX DisplayString
			MAX-ACCESS	read-only
			STATUS	current
			DESCRIPTION
			"Displays the port number."
			::= {ethernetOamEventLogStatEntry 1}

		ethernetOamEventLogStatLocalSymbolPeriod OBJECT-TYPE
			SYNTAX Counter
			MAX-ACCESS	read-only
			STATUS	current
			DESCRIPTION
			"Displays the number of error-symbol-period link events occurred on the local link."
			::= {ethernetOamEventLogStatEntry 2}

		ethernetOamEventLogStatRemoteSymbolPeriod OBJECT-TYPE
			SYNTAX Counter
			MAX-ACCESS	read-only
			STATUS	current
			DESCRIPTION
			"Displays the number of error-symbol-period link events occurred on the remote link."
			::= {ethernetOamEventLogStatEntry 3}

		ethernetOamEventLogStatLocalFrame OBJECT-TYPE
			SYNTAX Counter
			MAX-ACCESS	read-only
			STATUS	current
			DESCRIPTION
			"Displays the number of error-frame link events occurred on the local link."
			::= {ethernetOamEventLogStatEntry 4}

		ethernetOamEventLogStatRemoteFrame OBJECT-TYPE
			SYNTAX Counter
			MAX-ACCESS	read-only
			STATUS	current
			DESCRIPTION
			"Displays the number of error-frame link events occurred on the remote link."
			::= {ethernetOamEventLogStatEntry 5}

		ethernetOamEventLogStatLocalFramePeriod OBJECT-TYPE
			SYNTAX Counter
			MAX-ACCESS	read-only
			STATUS	current
			DESCRIPTION
			"Displays the number of error-frame-period link events occurred on the local link."
			::= {ethernetOamEventLogStatEntry 6}

		ethernetOamEventLogStatRemoteFramePeriod OBJECT-TYPE
			SYNTAX Counter
			MAX-ACCESS	read-only
			STATUS	current
			DESCRIPTION
			"Displays the number of error-frame-period link events occurred on the remote link."
			::= {ethernetOamEventLogStatEntry 7}

		ethernetOamEventLogStatLocalFrameSeconds OBJECT-TYPE
			SYNTAX Counter
			MAX-ACCESS	read-only
			STATUS	current
			DESCRIPTION
			"Displays the number of error-frame-seconds link events occurred on the local link or remote link."
			::= {ethernetOamEventLogStatEntry 8}

		ethernetOamEventLogStatRemoteFrameSeconds OBJECT-TYPE
			SYNTAX Counter
			MAX-ACCESS	read-only
			STATUS	current
			DESCRIPTION
			"Displays the number of error-frame-seconds link events occurred on the local link or remote link."
			::= {ethernetOamEventLogStatEntry 9}

		ethernetOamEventLogStatLocalDyingGasp OBJECT-TYPE
			SYNTAX Counter
			MAX-ACCESS	read-only
			STATUS	current
			DESCRIPTION
			"Displays the number of Dying Gasp link events occurred on the local link."
			::= {ethernetOamEventLogStatEntry 10}

		ethernetOamEventLogStatRemoteDyingGasp OBJECT-TYPE
			SYNTAX Counter
			MAX-ACCESS	read-only
			STATUS	current
			DESCRIPTION
			"Displays the number of Dying Gasp link events occurred on the remote link."
			::= {ethernetOamEventLogStatEntry 11}

		ethernetOamEventLogStatLocalCriticalEvent OBJECT-TYPE
			SYNTAX Counter
			MAX-ACCESS	read-only
			STATUS	current
			DESCRIPTION
			"Displays the number of Critical Event link events occurred on the local link."
			::= {ethernetOamEventLogStatEntry 12}

		ethernetOamEventLogStatRemoteCriticalEvent OBJECT-TYPE
			SYNTAX Counter
			MAX-ACCESS	read-only
			STATUS	current
			DESCRIPTION
			"Displays the number of Critical Event link events occurred on the remote link."
			::= {ethernetOamEventLogStatEntry 13}

		ethernetOamEventLogTable OBJECT-TYPE
			SYNTAX SEQUENCE OF EthernetOamEventLogEntry
			MAX-ACCESS	not-accessible
			STATUS	current
			DESCRIPTION
			"A table that contains the Ethernet OAM event log of each port."
			::= {ethernetOamEventLog 2}

		ethernetOamEventLogEntry OBJECT-TYPE
			SYNTAX EthernetOamEventLogEntry
			MAX-ACCESS	not-accessible
			STATUS	current
			DESCRIPTION
			"An entry that contains the Ethernet OAM event log of each port."
			INDEX {ifIndex, ethernetOamEventLogSeq}
			::= {ethernetOamEventLogTable 1}

		EthernetOamEventLogEntry ::=
		SEQUENCE
		{
			ethernetOamEventLogPort					DisplayString,
			ethernetOamEventLogSeq					INTEGER,
			ethernetOamEventLogType					INTEGER,
			ethernetOamEventLogLocation				INTEGER,
			ethernetOamEventLogTimestamp			OCTET STRING(SIZE(0..20)),
			ethernetOamEventLogValue				Counter,
			ethernetOamEventLogWindow				Counter,
			ethernetOamEventLogThreshold			Counter,
			ethernetOamEventLogAccumulatedErr		Counter64
		}

		ethernetOamEventLogPort OBJECT-TYPE
			SYNTAX DisplayString
			MAX-ACCESS	read-only
			STATUS	current
			DESCRIPTION
			"Displays the port number."
			::= {ethernetOamEventLogEntry 1}

		ethernetOamEventLogSeq OBJECT-TYPE
			SYNTAX INTEGER
			MAX-ACCESS	read-only
			STATUS	current
			DESCRIPTION
			"Displays the sequence number."
			::= {ethernetOamEventLogEntry 2}

		ethernetOamEventLogType OBJECT-TYPE
			SYNTAX INTEGER {symbol-period(1),frame(2),frame-period(3),frame-seconds(4),link-fault(16),dying-gasp(32),critical-event(48)}
			MAX-ACCESS	read-only
			STATUS	current
			DESCRIPTION
			"Displays the type of the link event."
			::= {ethernetOamEventLogEntry 3}

		ethernetOamEventLogLocation OBJECT-TYPE
			SYNTAX INTEGER {local(0),remote(1)}
			MAX-ACCESS	read-only
			STATUS	current
			DESCRIPTION
			"Displays the location when the link event ocurred."
			::= {ethernetOamEventLogEntry 4}

		ethernetOamEventLogTimestamp OBJECT-TYPE
			SYNTAX OCTET STRING(SIZE(0..20))
			MAX-ACCESS	read-only
			STATUS	current
			DESCRIPTION
			"Displays the timestamp when the link event ocurred."
			::= {ethernetOamEventLogEntry 5}

		ethernetOamEventLogValue OBJECT-TYPE
			SYNTAX Counter
			MAX-ACCESS	read-only
			STATUS	current
			DESCRIPTION
			"Displays the number of errors in the period."
			::= {ethernetOamEventLogEntry 6}

		ethernetOamEventLogWindow OBJECT-TYPE
			SYNTAX Counter
			MAX-ACCESS	read-only
			STATUS	current
			DESCRIPTION
			"Displays the period of the link event."
			::= {ethernetOamEventLogEntry 7}

		ethernetOamEventLogThreshold OBJECT-TYPE
			SYNTAX Counter
			MAX-ACCESS	read-only
			STATUS	current
			DESCRIPTION
			"Displays the number of errors that is required to be equal to or greater than in order for the event to be generated."
			::= {ethernetOamEventLogEntry 8}

		ethernetOamEventLogAccumulatedErr OBJECT-TYPE
			SYNTAX Counter64
			MAX-ACCESS	read-only
			STATUS	current
			DESCRIPTION
			"Displays the number of errors that have been detected since the OAM sublayer was reset."
			::= {ethernetOamEventLogEntry 9}

		ethernetOamEventLogClearTable OBJECT-TYPE
			SYNTAX SEQUENCE OF EthernetOamEventLogClearEntry
			MAX-ACCESS	not-accessible
			STATUS	current
			DESCRIPTION
			"You can clear both the statistics and log of link events of specified port in the table."
			::= {ethernetOamEventLog 3}

		ethernetOamEventLogClearEntry OBJECT-TYPE
			SYNTAX EthernetOamEventLogClearEntry
			MAX-ACCESS	not-accessible
			STATUS	current
			DESCRIPTION
			"You can clear both the statistics and log of link events of specified port in the entry."
			INDEX {ifIndex}
			::= {ethernetOamEventLogClearTable 1}

		EthernetOamEventLogClearEntry ::=
		SEQUENCE
		{
			ethernetOamEventLogClearPort	DisplayString,
			ethernetOamEventLogClearAction	INTEGER
		}

		ethernetOamEventLogClearPort OBJECT-TYPE
			SYNTAX DisplayString
			MAX-ACCESS	read-only
			STATUS	current
			DESCRIPTION
			"Displays the port number."
			::= {ethernetOamEventLogClearEntry 1}

		ethernetOamEventLogClearAction OBJECT-TYPE
			SYNTAX INTEGER {unchange(0),clear(1)}
			MAX-ACCESS	read-write
			STATUS	current
			DESCRIPTION
			"Clear both the statistics and log of link events of specified port."
			::= {ethernetOamEventLogClearEntry 2}

END
