TPLINK-SDM-MIB	DEFINITIONS ::= BEGIN
    IMPORTS
		tplinkMgmt
			FROM TPLINK-MIB
		DisplayString
      		FROM SNMPv2-TC
        OBJECT-TYPE
          	FROM SNMPv2-SMI;

	tplinkSDMMIB MODULE-IDENTITY
		LAST-UPDATED    "201212130930Z"
		ORGANIZATION    "TPLINK"
		CONTACT-INFO    "www.tplink.com"
		DESCRIPTION	    "Private MIB for SDM configuration."
		REVISION        "201212130930Z"
		DESCRIPTION
			"Initial version of this MIB module."
		::= { tplinkMgmt 90 }

	tplinkSDMMIBObjects	OBJECT IDENTIFIER ::= { tplinkSDMMIB 1 }
	tplinkSDMNotifications	OBJECT IDENTIFIER ::= { tplinkSDMMIB 2 }

	sdmTemLayOutTable OBJECT-TYPE
		SYNTAX		SEQUENCE OF SdmTemLayOutEntry
		MAX-ACCESS  not-accessible
		STATUS		current
		DESCRIPTION
	               "Display the layout of templates."
		::= { tplinkSDMMIBObjects 1 }

	sdmTemLayOutEntry OBJECT-TYPE
		SYNTAX      SdmTemLayOutEntry
		MAX-ACCESS  not-accessible
		STATUS      current
		DESCRIPTION
			"An entry contains of the layout of some template."
		INDEX
		{
			sdmTemName
		}
		::= { sdmTemLayOutTable 1 }

	SdmTemLayOutEntry ::=
	SEQUENCE
	{
    sdmTemName      		DisplayString,
    ipAclRuleNum    		INTEGER,
		macAclRuleNum	  		INTEGER,
		combinedAclRuleNum	INTEGER,
		ipv6AclRuleNum			INTEGER,
		v4SourceNum					INTEGER,
		v6SourceNum					INTEGER,
		packetContentAclNum	INTEGER
	}

	sdmTemName OBJECT-TYPE
		SYNTAX      DisplayString
		MAX-ACCESS  read-only
		STATUS      current
		DESCRIPTION
			"Display the name of templates."
		::= { sdmTemLayOutEntry 1 }


   ipAclRuleNum OBJECT-TYPE
		SYNTAX		INTEGER
		MAX-ACCESS  read-only
		STATUS		current
		DESCRIPTION
		 "Display the number of TCAM entries for IP ACL Rules, which include Lay3 ACL Rules and Lay4 ACL Rules."
		::= { sdmTemLayOutEntry 2 }

   macAclRuleNum OBJECT-TYPE
		SYNTAX		INTEGER
		MAX-ACCESS  read-only
		STATUS		current
		DESCRIPTION
		 "Display the number of TCAM entries for Lay2 ACL Rules."
		::= { sdmTemLayOutEntry 3 }

   combinedAclRuleNum OBJECT-TYPE
		SYNTAX		INTEGER
		MAX-ACCESS  read-only
		STATUS		current
		DESCRIPTION
		 "Display the number of TCAM entries for Combined ACL Rules."
		::= { sdmTemLayOutEntry 4 }

   ipv6AclRuleNum OBJECT-TYPE
		SYNTAX		INTEGER
		MAX-ACCESS  read-only
		STATUS		current
		DESCRIPTION
		 "Display the number of TCAM entries for IPv6 ACL Rules."
		::= { sdmTemLayOutEntry 5 }

   v4SourceNum OBJECT-TYPE
		SYNTAX		INTEGER
		MAX-ACCESS  read-only
		STATUS      current
		DESCRIPTION
		   "Display the number of TCAM entries for IPV4 Source Guard."
		::= { sdmTemLayOutEntry 6 }

   v6SourceNum OBJECT-TYPE
		SYNTAX		INTEGER
		MAX-ACCESS  read-only
		STATUS      current
		DESCRIPTION
		   "Display the number of TCAM entries for IPV6 Source Guard."
		::= { sdmTemLayOutEntry 7 }

   packetContentAclNum OBJECT-TYPE
		SYNTAX		INTEGER
		MAX-ACCESS  read-only
		STATUS      current
		DESCRIPTION
		   "Display the number of TCAM entries for Packet Content ACL."
		::= { sdmTemLayOutEntry 8 }

	sdmCurTemName OBJECT-TYPE
		SYNTAX 		DisplayString
		MAX-ACCESS	read-only
		STATUS		current
		DESCRIPTION
			   "Display the template currently in effect."
		::= { tplinkSDMMIBObjects 2 }

	sdmNextTemID OBJECT-TYPE
		SYNTAX  INTEGER
		{
			default(0),
			enterpriseV4(1),
			enterpriseV6(2)
		}
		MAX-ACCESS  read-write
		STATUS		current
		DESCRIPTION
			   "Select a template which will take effect after reboot the switch.
				The value can be one of following:
				'default';
				'enterpriseV4';
				'enterpriseV6'."
		::= { tplinkSDMMIBObjects 3 }



END
