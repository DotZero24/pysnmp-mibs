EAP-CLIENT-MIB   DEFINITIONS ::= BEGIN

IMPORTS
    MODULE-IDENTITY
        FROM SNMPv2-SMI
    eap
        FROM TPLINK-MIB;

clientStatis        MODULE-IDENTITY
LAST-UPDATED        "201610170000z"
ORGANIZATION        "TPLINK"
CONTACT-INFO        "www.tplink.com"
DESCRIPTION
                    "Private MIB for clients statistics."
REVISION            "201610170000z"
DESCRIPTION
            "Initial version of this MIB module."
::= { eap 1 }

clientCount OBJECT-TYPE
      SYNTAX  INTEGER	(1..1000)
              MAX-ACCESS  read-only
              STATUS  current
              DESCRIPTION
                      "this used to get the count of clients"
              ::= { clientStatis 1 }
clientTable    OBJECT IDENTIFIER  ::= { clientStatis 2 }
END
