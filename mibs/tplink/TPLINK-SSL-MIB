TPLINK-SSL-MIB	DEFINITIONS ::= BEGIN
	IMPORTS
		MODULE-IDENTITY, OBJECT-TYPE
			FROM SNMPv2-SMI
	    tplinkMgmt
			FROM TPLINK-MIB;

      	tplinkSslMIB MODULE-IDENTITY
			LAST-UPDATED    "201212130930Z"
			ORGANIZATION    "TPLINK"
			CONTACT-INFO    "www.tplink.com"
			DESCRIPTION	    "Private MIB for SSL configuration."
			REVISION        "201212130930Z"
			DESCRIPTION
					"Initial version of this MIB module."
			::= { tplinkMgmt 42 }

			tplinkSslMIBObjects OBJECT IDENTIFIER ::= {tplinkSslMIB 1}
        	tplinkSslNotifications OBJECT IDENTIFIER ::= {tplinkSslMIB 2}

      	    tpHttpsEnable OBJECT-TYPE
	          SYNTAX  INTEGER{
	      		disable(0),
	      		enable(1)
	      		}
	            MAX-ACCESS  read-write
	            STATUS  current
	            DESCRIPTION
	                    "0. disable
	                     1. enable"
	            ::= { tplinkSslMIBObjects 1 }

			tpSslProtocolVersion OBJECT-TYPE
	          SYNTAX  INTEGER{
	      		sslv3(1),
	      		tlsv1(2),
				tlsv11(3),
				tlsv12(4),
				all(5)
	      		}
	            MAX-ACCESS  read-write
	            STATUS  current
	            DESCRIPTION
	                    "1. SSLv3
	                     2. TLSv1.0
						 3. TLSv1.1
						 4. TLSv1.2
						 5. ALL"
	            ::= { tplinkSslMIBObjects 2 }

			tpRc4Md5 OBJECT-TYPE
	          SYNTAX  INTEGER{
	      		disable(0),
	      		enable(1)
	      		}
	            MAX-ACCESS  read-write
	            STATUS  current
	            DESCRIPTION
	                    "0. disable
	                     1. enable"
	            ::= { tplinkSslMIBObjects 3 }

			tpRc4Sha OBJECT-TYPE
	          SYNTAX  INTEGER{
	      		disable(0),
	      		enable(1)
	      		}
	            MAX-ACCESS  read-write
	            STATUS  current
	            DESCRIPTION
	                    "0. disable
	                     1. enable"
	            ::= { tplinkSslMIBObjects 4 }

			tpDesCbcSha OBJECT-TYPE
	          SYNTAX  INTEGER{
	      		disable(0),
	      		enable(1)
	      		}
	            MAX-ACCESS  read-write
	            STATUS  current
	            DESCRIPTION
	                    "0. disable
	                     1. enable"
	            ::= { tplinkSslMIBObjects 5 }

			tp3DesEdeCbcSha OBJECT-TYPE
	          SYNTAX  INTEGER{
	      		disable(0),
	      		enable(1)
	      		}
	            MAX-ACCESS  read-write
	            STATUS  current
	            DESCRIPTION
	                    "0. disable
	                     1. enable"
	            ::= { tplinkSslMIBObjects 6 }

			tpEcdheAes128GcmSha256 OBJECT-TYPE
	          SYNTAX  INTEGER{
	      		disable(0),
	      		enable(1)
	      		}
	            MAX-ACCESS  read-write
	            STATUS  current
	            DESCRIPTION
	                    "0. disable
	                     1. enable
	                     Disable or enable TLS_ECDHE_RSA_WITH_AES_128_GCM_SHA256 and TLS_ECDHE_ECDSA_WITH_AES_128_GCM_SHA256 cipher suite."
	            ::= { tplinkSslMIBObjects 7 }

			tpEcdheAes256GcmSha384 OBJECT-TYPE
	          SYNTAX  INTEGER{
	      		disable(0),
	      		enable(1)
	      		}
	            MAX-ACCESS  read-write
	            STATUS  current
	            DESCRIPTION
	                    "0. disable
	                     1. enable
	                     Disable or enable TLS_ECDHE_RSA_WITH_AES_256_GCM_SHA384 and TLS_ECDHE_ECDSA_WITH_AES_256_GCM_SHA384 cipher suite."
	            ::= { tplinkSslMIBObjects 8 }

      	    tpHttpsSessionTimeOut	OBJECT-TYPE
			SYNTAX		INTEGER (5..30)
			MAX-ACCESS	read-write
			STATUS		current
			DESCRIPTION	"HTTPS session timeout in minutes."
	            ::= { tplinkSslMIBObjects 9 }

			tpHttpsUserLimitEnable	OBJECT-TYPE
			SYNTAX  INTEGER{
					disable(0),
					enable(1)
					}
			MAX-ACCESS	read-write
			STATUS		current
			DESCRIPTION
						"0. disable
						1.enable"
	            ::= { tplinkSslMIBObjects 10 }

			tpHttpsUserLimitMaxAdminNum	OBJECT-TYPE
			SYNTAX  INTEGER
			MAX-ACCESS	read-write
			STATUS		current
			DESCRIPTION	"The max num of users as Admin. You should enable HTTPS user number limiting before setting this object."
	            ::= { tplinkSslMIBObjects 11 }

			tpHttpsUserLimitMaxOperatorNum	OBJECT-TYPE
			SYNTAX  INTEGER
			MAX-ACCESS	read-write
			STATUS		current
			DESCRIPTION "The max num of users as Operator. You should enable HTTP user number limiting before setting this object."
	            ::= { tplinkSslMIBObjects 12 }

			tpHttpsUserLimitMaxPowerUserNum	OBJECT-TYPE
			SYNTAX  INTEGER
			MAX-ACCESS	read-write
			STATUS		current
			DESCRIPTION "The max num of users as Power User. You should enable HTTP user number limiting before setting this object."
	            ::= { tplinkSslMIBObjects 13 }

			tpHttpsUserLimitMaxUserNum	OBJECT-TYPE
			SYNTAX  INTEGER
			MAX-ACCESS	read-write
			STATUS		current
			DESCRIPTION "The max num of users as User. You should enable HTTP user number limiting before setting this object."
	            ::= { tplinkSslMIBObjects 14 }

			tpHttpsPort	OBJECT-TYPE
			SYNTAX		INTEGER (1..65535)
			MAX-ACCESS	read-write
			STATUS		current
			DESCRIPTION	"Secure HTTP server port number."
				::= { tplinkSslMIBObjects 15 }
          END
