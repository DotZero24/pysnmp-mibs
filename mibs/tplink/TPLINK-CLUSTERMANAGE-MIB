TPLINK-CLUSTERMANAGE-MIB DEFINITIONS ::= BEGIN
		IMPORTS
		OBJECT-TYPE
			  	         	FROM SNMPv2-SMI
		clusterManage
							FROM TPLINK-CLUSTER-MIB;

   		clusterRole OBJECT-TYPE
   			SYNTAX
   				INTEGER
   				{
   					commander(0),
   					member(1),
   					candidate(2),
   					individual(3)
   				}
   			MAX-ACCESS		read-write
   			STATUS				current
   			DESCRIPTION
   			"This object indicates the current role of the switch.
   			You can not set the role to commander with this object.
   			You can set the role to candidate when the role is commander.
   			You can set the role to individual when the role is candidate or member.
   			You can set the role to candidate when the role is individual."
   			::=	{clusterManage 1}
END
