TPLINK-L2PROTOCOL-TUNNEL-MIB DEFINITIONS ::= BEGIN
	IMPORTS
		OBJECT-TYPE,MODULE-IDENTITY, Counter32, Integer32, OBJECT-IDENTITY, NOTIFICATION-TYPE
			  	         	FROM SNMPv2-SMI
		ifIndex
				FROM RFC1213-MIB
		tplinkMgmt
				FROM TPLINK-MIB;

	tplinkL2protocolTunnelMIB MODULE-IDENTITY
	    LAST-UPDATED    "200908270000Z"
	    ORGANIZATION    "TPLINK"
	    CONTACT-INFO		"www.tplink.com"
	    DESCRIPTION			"The config of layer 2 protocol tunnel."
	    REVISION        "200908270000Z"
	    DESCRIPTION			"Initial version of this MIB module."
	    ::= { tplinkMgmt 81 }

	tplinkL2protocolTunnelMIBObjects			OBJECT IDENTIFIER	::= { tplinkL2protocolTunnelMIB 1 }
	tplinkL2protocolTunnelNotifications	        OBJECT IDENTIFIER 	::= { tplinkL2protocolTunnelMIB 2 }

	tpL2ptGlobalCfg OBJECT IDENTIFIER ::= { tplinkL2protocolTunnelMIBObjects 1 }
	    tpL2ptEnable OBJECT-TYPE
         			SYNTAX  INTEGER{
	      							disable(0), 						--disable
	      							enable(1)							--enable
	      							}
              MAX-ACCESS  read-write
              STATUS  current
              DESCRIPTION
                      "Select Enable/Disable l2protocol tunnel function globally on the Switch.
                      0. disable
                      1. enable"
              ::= { tpL2ptGlobalCfg 1 }

	tpL2ptPortCfg OBJECT IDENTIFIER ::= { tplinkL2protocolTunnelMIBObjects 2 }
	   		tpL2ptPortTable OBJECT-TYPE
              SYNTAX  SEQUENCE OF TPL2PTPORTENTRY
              MAX-ACCESS  not-accessible
              STATUS  current
              DESCRIPTION
                      "A list of port loopback detection."
              ::= { tpL2ptPortCfg 1 }


         tpL2ptPortEntry OBJECT-TYPE
              SYNTAX  TPL2PTPORTENTRY
              MAX-ACCESS  not-accessible
              STATUS  current
              DESCRIPTION
                      "The entry of the port l2protocol tunnel list ."
              INDEX   { ifIndex }
              ::= { tpL2ptPortTable 1 }


        TPL2PTPORTENTRY ::=
              SEQUENCE {
				  tpL2ptPort
						OCTET STRING,
                  tpL2ptType
                  		INTEGER{
	      										none(0), 					--Disable
	      										uni(1),						--User to network interface
                                                nni(2)						--Network to network interface
	      											},
                  tpL2ptProtocol
                  		OCTET STRING,
                  tpL2ptThreshold
                  		OCTET STRING,
                  tpL2ptLag
                        OCTET STRING
              }
              	tpL2ptPort OBJECT-TYPE
					SYNTAX  	OCTET STRING
						(SIZE (0..255))
					MAX-ACCESS  read-only
					STATUS  	current
					DESCRIPTION
						"Display port number"
				::= { tpL2ptPortEntry 1 }

			    tpL2ptType  OBJECT-TYPE
			     SYNTAX  INTEGER{
	      										none(0), 					--Disable
	      										uni(1),						--User to network interface
                                                nni(2)						--Network to network interface
	      											}
			      MAX-ACCESS  read-write
			      STATUS  current
			      DESCRIPTION
			              "The type of the port."
			      ::= { tpL2ptPortEntry 2 }

			    tpL2ptProtocol  OBJECT-TYPE
			     SYNTAX  OCTET STRING (SIZE (0..255))
			      MAX-ACCESS  read-write
			      STATUS  current
			      DESCRIPTION
			              "The tunnel protocol of the port."
			      ::= { tpL2ptPortEntry 3 }

			    tpL2ptThreshold OBJECT-TYPE
			     SYNTAX  OCTET STRING (SIZE (0..255))
			      MAX-ACCESS  read-write
			      STATUS  current
			      DESCRIPTION
			              "Set drop threshold for protocol packets."
			      ::= { tpL2ptPortEntry 4 }
				tpL2ptLag OBJECT-TYPE
					SYNTAX OCTET STRING
						(SIZE (0..255))
					MAX-ACCESS
						read-only
					STATUS
						current
					DESCRIPTION
						"Displays the LAG number which the port belongs to."
					::= { tpL2ptPortEntry 5 }
END
