TPLINK-RIP-MIB	DEFINITIONS ::= BEGIN
	IMPORTS
		MODULE-IDENTITY, OBJECT-TYPE, IpAddress
			FROM SNMPv2-SMI
	    TPRowStatus
  			FROM TPLINK-TC-MIB
		tplinkMgmt
			FROM TPLINK-MIB;


	tplinkRipMIB MODULE-IDENTITY
		LAST-UPDATED    "201212130930Z"
		ORGANIZATION    "TPLINK"
		CONTACT-INFO    "www.tplink.com"
		DESCRIPTION	    "Private MIB for RIP configuration."
		REVISION        "201212130930Z"
		DESCRIPTION
				"Initial version of this MIB module."
		::= { tplinkMgmt 40 }

      	tplinkRipMIBObjects OBJECT IDENTIFIER ::= {tplinkRipMIB 1}
        tplinkRipNotifications OBJECT IDENTIFIER ::= {tplinkRipMIB 2}

	    tpRipBasicConfig	  		OBJECT IDENTIFIER ::= {tplinkRipMIBObjects 1}
        tpRipNetworkConfig 		OBJECT IDENTIFIER ::= {tplinkRipMIBObjects 2}
        tpRipInterfaceConfig 		OBJECT IDENTIFIER ::= {tplinkRipMIBObjects 3}
        tpRipRouteItems 			OBJECT IDENTIFIER ::= {tplinkRipMIBObjects 4}

        tpRipProtocolCtrl OBJECT-TYPE
            SYNTAX  INTEGER{
	      		disable(0), 						--disable
	      		enable(1)								--enable
	      	}
            MAX-ACCESS  read-write
            STATUS  current
            DESCRIPTION
                     "Enable or disable the RIP function on the switch."
        ::= { tpRipBasicConfig 1 }

         tpRipProtocolVersion OBJECT-TYPE
            SYNTAX  INTEGER{
            	default(0),
	      		ripv1(1), 						--V1
	      		ripv2(2)								--V2	      	}
            }
            MAX-ACCESS  read-write
            STATUS  current
            DESCRIPTION
                     "Choose the global RIP version."
        ::= { tpRipBasicConfig 2 }

        tpRipDistance OBJECT-TYPE
        	SYNTAX INTEGER  (1..255)
        	MAX-ACCESS  read-write
            STATUS  current
            DESCRIPTION
                     "Set the RIP router distance."
        ::= { tpRipBasicConfig 3 }

        tpRipAutoSumm OBJECT-TYPE
            SYNTAX  INTEGER{
	      		disable(0), 						--disable
	      		enable(1)								--enable
	      	}
            MAX-ACCESS  read-write
            STATUS  current
            DESCRIPTION
                     "If you select enable groups of adjacent routes will be summarized into single entries."
        ::= { tpRipBasicConfig 4 }

        tpRipDefaultMetric OBJECT-TYPE
        	SYNTAX INTEGER  (1..15)
        	MAX-ACCESS  read-write
            STATUS  current
            DESCRIPTION
                     "Set the default metric for redistributed routes."
        ::= { tpRipBasicConfig 5 }

         tpRipRedistriStatic OBJECT-TYPE
            SYNTAX  INTEGER{
	      		disable(0), 						--disable
	      		enable(1)								--enable
	      	}
            MAX-ACCESS  read-write
            STATUS  current
            DESCRIPTION
                     "Choose to distribute Static router entries to RIP,the default is disable."
        ::= { tpRipBasicConfig 6 }

        tpRipRedistriOspf OBJECT-TYPE
            SYNTAX  INTEGER{
	      		disable(0), 						--disable
	      		enable(1)								--enable
	      	}
            MAX-ACCESS  read-write
            STATUS  current
            DESCRIPTION
                     "Choose to distribute OSPF router entries to RIP,the default is disable.."
        ::= { tpRipBasicConfig 7 }

         tpRipRedistStaticMetric OBJECT-TYPE
        	SYNTAX INTEGER  (1..15)
        	MAX-ACCESS  read-write
            STATUS  current
            DESCRIPTION
                     "Set the metric for redistributed static routes."
        ::= { tpRipBasicConfig 8 }

 		tpRipRedistOspfMetric OBJECT-TYPE
        	SYNTAX INTEGER  (1..15)
        	MAX-ACCESS  read-write
            STATUS  current
            DESCRIPTION
                     "Set the metric for redistributed OSPF routes."
        ::= { tpRipBasicConfig 9 }


        tpRipUpdateTimer OBJECT-TYPE
        	SYNTAX INTEGER  (1..100)
        	MAX-ACCESS  read-write
            STATUS  current
            DESCRIPTION
                     "The timer interval to generate a complete response to every neighboring gateway."
        ::= { tpRipBasicConfig 10 }

        tpRipTimeOutTimer OBJECT-TYPE
        	SYNTAX INTEGER  (1..300)
        	MAX-ACCESS  read-write
            STATUS  current
            DESCRIPTION
                     "Upon expiration of the timeout, the route is no longer valid and setted to unreachable. "
        ::= { tpRipBasicConfig 11 }

        tpRipGarbageTimer OBJECT-TYPE
        	SYNTAX INTEGER  (1..500)
        	MAX-ACCESS  read-write
            STATUS  current
            DESCRIPTION
                     "Upon expiration of the garbage-collection timer, the route is finally removed from the tables."
        ::= { tpRipBasicConfig 12 }




        tpRipNetworkTable OBJECT-TYPE
        	SYNTAX SEQUENCE OF RIPNETWORKENTRY
        	MAX-ACCESS not-accessible
        	STATUS current
        	DESCRIPTION
        			"The list of rip network."
        	::= {tpRipNetworkConfig 1}

        tpRipNetworkEntry OBJECT-TYPE
        	SYNTAX RIPNETWORKENTRY
        	MAX-ACCESS not-accessible
        	STATUS current
        	DESCRIPTION
        			"RIP network entries."
        	INDEX {tpRipNetworkAddress}
        	::= {tpRipNetworkTable 1}

        RIPNETWORKENTRY ::=
        	SEQUENCE {
        			tpRipNetworkAddress
        	         	IpAddress,
					tpRipNetworkStatus
						TPRowStatus
					}


         tpRipNetworkAddress OBJECT-TYPE
         	SYNTAX IpAddress
         	MAX-ACCESS read-create
         	STATUS current
         	DESCRIPTION
         				"RIP network IP address."
         	::= {tpRipNetworkEntry 1}

         tpRipNetworkStatus OBJECT-TYPE
            SYNTAX  TPRowStatus
            MAX-ACCESS  read-create
            STATUS  current
            DESCRIPTION
                     " The following values are states:
                     these values may be used as follow:
                     active(1),if the entry is being used.
                     notInService(2),destory the entry.
                     notReady(3),destory the entry.
                     createAndGo(4),not being used
                     createAndWait(5),creat a new entry
                     destroy(6),destory the entry."
         	::={ tpRipNetworkEntry 2 }

        tpRipInterfaceTable OBJECT-TYPE
        	SYNTAX SEQUENCE OF RIPINTERFACEENTRY
        	MAX-ACCESS not-accessible
        	STATUS current
        	DESCRIPTION
        			"The list of rip interfaces."
        	::= {tpRipInterfaceConfig 1}

        tpRipInterfaceEntry OBJECT-TYPE
        	SYNTAX RIPINTERFACEENTRY
        	MAX-ACCESS not-accessible
        	STATUS current
        	DESCRIPTION
        			"Config the RIP parameters of the interface."
        	INDEX {tpRipInterfaceID}
        	::= {tpRipInterfaceTable 1}

        RIPINTERFACEENTRY ::=
        	SEQUENCE {
        			tpRipInterfaceID
        	         	OCTET STRING (SIZE (0..25)),
        	        tpRipInterfaceStatus
        	        	OCTET STRING (SIZE (0..10)),
        	        tpRipInterfaceSendVersion
        	        	INTEGER  {ripv1(1), ripv2(2), rip-1c(3)},
        	        tpRipInterfaceRecvVersion
        	        	INTEGER  {ripv1(1), ripv2(2), both(3)},
        	        tpRipInterfaceRIPv2Broad
        	        	INTEGER  {disable(0), enable(1)},
        	        tpRipInterfaceAuthMode
        	        	INTEGER  {none(1), simple(2), md5(3)},
        	        tpRipInterfaceKeyID
        	        	INTEGER (0..255),
        	        tpRipInterfaceKey
        	        	OCTET STRING (SIZE (0..16)),
        	        tpRipInterfaceSplitHorizon
        	        	INTEGER  {disable(0), enable(1)},
        	        tpRipInterfacePoisonReverse
        	        	INTEGER  {disable(0), enable(1)}
					}


         tpRipInterfaceID OBJECT-TYPE
         	SYNTAX OCTET STRING (SIZE (0..25))
         	MAX-ACCESS read-only
         	STATUS current
         	DESCRIPTION
         				"The interface IP address and subnet mask."
         	::= {tpRipInterfaceEntry 1}

         tpRipInterfaceStatus OBJECT-TYPE
         	SYNTAX OCTET STRING (SIZE (0..10))
         	MAX-ACCESS read-only
         	STATUS current
         	DESCRIPTION
         				"The interface RIP status(up or down)."
         	::= {tpRipInterfaceEntry 2}

         	tpRipInterfaceSendVersion OBJECT-TYPE
        	  SYNTAX INTEGER  {ripv1(1), ripv2(2), rip-1c(3)}
        	  MAX-ACCESS read-write
        	  STATUS current
        	  DESCRIPTION
        	  			"Select the version of RIP control packets sended from the interface."
        	 ::= {tpRipInterfaceEntry 3}

        	tpRipInterfaceRecvVersion OBJECT-TYPE
        	  SYNTAX INTEGER  {ripv1(1), ripv2(2), both(3)}
        	  MAX-ACCESS read-write
        	  STATUS current
        	  DESCRIPTION
        	  			"Select the version of RIP control packets received from the interface."
        	 ::= {tpRipInterfaceEntry 4}

             tpRipInterfaceRIPv2Broad OBJECT-TYPE
        	  SYNTAX INTEGER  {disable(0), enable(1)}
        	  MAX-ACCESS read-write
        	  STATUS current
        	  DESCRIPTION
        	  			"Send RIP version 2 formatted packets via broadcast."
        	 ::= {tpRipInterfaceEntry 5}


        	 tpRipInterfaceAuthMode OBJECT-TYPE
        	  SYNTAX  INTEGER  {none(1), simple(2), md5(3)}
        	  MAX-ACCESS read-write
        	  STATUS current
        	  DESCRIPTION
        	  			"Select an authentication type."
        	 ::= {tpRipInterfaceEntry 6}

		    tpRipInterfaceKeyID OBJECT-TYPE
         	SYNTAX INTEGER (0..255)
         	MAX-ACCESS read-write
         	STATUS current
         	DESCRIPTION
         				"Enter the RIP Authentication Key ID for the specified interface."
         	::= {tpRipInterfaceEntry 7}

         	tpRipInterfaceKey OBJECT-TYPE
         	SYNTAX OCTET STRING (SIZE (0..16))
         	MAX-ACCESS read-write
         	STATUS current
         	DESCRIPTION
         				"Enter the RIP Authentication Key for the specified interface. "
         	::= {tpRipInterfaceEntry 8}

         	tpRipInterfaceSplitHorizon OBJECT-TYPE
        	  SYNTAX INTEGER  {disable(0), enable(1)}
        	  MAX-ACCESS read-write
        	  STATUS current
        	  DESCRIPTION
        	  			"Enable or disable the split horizon."
        	 ::= {tpRipInterfaceEntry 9}

        	 tpRipInterfacePoisonReverse OBJECT-TYPE
        	  SYNTAX INTEGER  {disable(0), enable(1)}
        	  MAX-ACCESS read-write
        	  STATUS current
        	  DESCRIPTION
        	  			"Enable or disable the poison reverse."
        	 ::= {tpRipInterfaceEntry 10}



       tpRipRouteTable OBJECT-TYPE
       	SYNTAX SEQUENCE OF RIPROUTEENTRY
       	MAX-ACCESS not-accessible
       	STATUS current
       	DESCRIPTION
       			"Display the route entries generated by RIP protocol."
       	::= {tpRipRouteItems 1}

       	tpRipRouteEntry OBJECT-TYPE
       		SYNTAX RIPROUTEENTRY
       		MAX-ACCESS not-accessible
       		STATUS current
       		DESCRIPTION
       			"RIP route entries."
       		INDEX {tpRipIpAddressMask}
       	::={tpRipRouteTable 1}

        RIPROUTEENTRY ::=
        	SEQUENCE {
        		tpRipIpAddressMask
        			OCTET STRING (SIZE (0..25)),
        		tpRipGateway
        			IpAddress,
        		tpRipMetric
        			INTEGER (1..15),
        		tpRipInterfaceName
        			OCTET STRING (SIZE (0..25)),
        		tpRipTimers
        			INTEGER (1..300)

        	     }

        tpRipIpAddressMask OBJECT-TYPE
         	SYNTAX OCTET STRING (SIZE (0..25))
         	MAX-ACCESS read-only
         	STATUS current
         	DESCRIPTION
         				"The destination IP address and subnet mask."
         	::= {tpRipRouteEntry 1}

         tpRipGateway OBJECT-TYPE
         	SYNTAX IpAddress
         	MAX-ACCESS read-only
         	STATUS current
         	DESCRIPTION
         				"The gateway interface to send the data packet."
         	::= {tpRipRouteEntry 2}

         tpRipMetric OBJECT-TYPE
         	SYNTAX INTEGER (1..15)
         	MAX-ACCESS read-only
         	STATUS current
         	DESCRIPTION
         				"The metric to reach the destination IP address."
         	::= {tpRipRouteEntry 3}

         tpRipInterfaceName OBJECT-TYPE
         	SYNTAX OCTET STRING (SIZE (0..25))
         	MAX-ACCESS read-only
         	STATUS current
         	DESCRIPTION
         				"The gateway interface name."
         	::= {tpRipRouteEntry 4}

         tpRipTimers OBJECT-TYPE
         	SYNTAX INTEGER (1..300)
         	MAX-ACCESS read-only
         	STATUS current
         	DESCRIPTION
         				"The time of the route entry."
         	::= {tpRipRouteEntry 5}



       END
