TPLINK-CLUSTERTREE-MIB DEFINITIONS ::= BEGIN

       IMPORTS
       		MODULE-IDENTITY
        	  	         	FROM SNMPv2-SMI
            tplinkMgmt
					FROM TPLINK-MIB;


		tplinkClusterTreeMIB MODULE-IDENTITY
		LAST-UPDATED    "201212130930Z"
		ORGANIZATION    "TPLINK"
		CONTACT-INFO    "www.tplink.com.cn"
		DESCRIPTION	    "Private MIB for Cluster."
		REVISION        "201212130930Z"
		DESCRIPTION
				"Initial version of this MIB module."
		::= { tplinkMgmt 33 }

		tplinkClusterMIBObjects 		OBJECT IDENTIFIER ::= {tplinkClusterTreeMIB 1}
		tplinkClusterNotifications 	    OBJECT IDENTIFIER ::= {tplinkClusterTreeMIB 2}
 END
