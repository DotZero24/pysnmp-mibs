TPLINK-pppoeConfig-MIB DEFINITIONS ::= BEGIN

	IMPORTS
		MODULE-IDENTITY, OBJECT-TYPE, IpAddress
			FROM SNMPv2-SMI
		tplinkMgmt
			FROM TPLINK-MIB
		ifIndex
			FROM RFC1213-MIB
		DisplayString
			FROM SNMPv2-TC;

	tplinkPPPoEConfigMIB MODULE-IDENTITY
		LAST-UPDATED    "201212171050Z"
		ORGANIZATION    "TPLINK"
		CONTACT-INFO    "www.tplink.com"
		DESCRIPTION	    "Private MIB for PPPoE Circuit ID configuration."
		REVISION        "201212171050Z"
		DESCRIPTION
				"Initial version of this MIB module."
		::= { tplinkMgmt 57 }


	tplinkPPPoEConfigMIBObjects		OBJECT IDENTIFIER	::= { tplinkPPPoEConfigMIB 1 }
	tplinkPPPoEConfigNotifications	OBJECT IDENTIFIER	::= { tplinkPPPoEConfigMIB 2 }

		tpPppoeIdInsertionGlobalConfig  		OBJECT IDENTIFIER ::= {tplinkPPPoEConfigMIBObjects 1}

				tpPppoeIdInsertionGlobalEnable OBJECT-TYPE
	          SYNTAX  INTEGER{
	      		disable(0),
	      		enable(1)
	      		}
	            MAX-ACCESS  read-write
	            STATUS  current
	            DESCRIPTION
	                    "0. disable
	                     1. enable
	                     Enable/Disable the PPPoE Circuit-ID function."
	            ::= { tpPppoeIdInsertionGlobalConfig 1 }

       -- the PPPoE Circuit-ID port config
	tpPppoeIdInsertionPortConfig 			OBJECT IDENTIFIER ::= {tplinkPPPoEConfigMIBObjects 2}

       tpPppoeIdInsertionPortConfigTable OBJECT-TYPE
          SYNTAX  SEQUENCE OF PPPOEIDINSERTIONPORTCONFIGENTRY
          MAX-ACCESS  not-accessible
          STATUS  current
          DESCRIPTION
                  "A list of PPPoE Circuit-Id port config entries."
          ::= { tpPppoeIdInsertionPortConfig 1 }

      tpPppoeIdInsertionPortConfigEntry OBJECT-TYPE
          SYNTAX  PPPOEIDINSERTIONPORTCONFIGENTRY
          MAX-ACCESS  not-accessible
          STATUS  current
          DESCRIPTION
                  "An entry contains of the information of PPPoE Circuit-ID port config.
                   Here you can configure the ports for the PPPoE Circuit-ID."
          INDEX   {ifIndex }
          ::= { tpPppoeIdInsertionPortConfigTable 1 }

      PPPOEIDINSERTIONPORTCONFIGENTRY ::=
          SEQUENCE {
							tpPppoeIdInsertionPortIndex
									DisplayString,
							tpPppoeCircuitIdPortConfigEnable
									INTEGER,
							tpPppoeCircuitIdPortConfigIdType
									INTEGER,
							tpPppoeCircuitIdPortConfigUdfValue
									OCTET STRING (SIZE (0..40)),
							tpPppoeRemoteIdPortConfigEnable
									INTEGER,
							tpPppoeRemoteIdPortConfigValue
									OCTET STRING (SIZE (0..40))
          }

  		tpPppoeIdInsertionPortIndex OBJECT-TYPE
  			SYNTAX			DisplayString(SIZE(0..16))
  			MAX-ACCESS	read-only
  			STATUS			current
  			DESCRIPTION
  			"This object indicates the port number."
  			::= {tpPppoeIdInsertionPortConfigEntry 1 }

      tpPppoeCircuitIdPortConfigEnable OBJECT-TYPE
          SYNTAX  INTEGER{
      		disable(0),
      		enable(1)
      		}
          MAX-ACCESS  read-write
          STATUS  current
          DESCRIPTION
                  "0. disable
                   1. enable
                   Select Enable/Disable the PPPoE Circuit-ID Insertion feature for the port."
          ::= { tpPppoeIdInsertionPortConfigEntry 2 }

      tpPppoeCircuitIdPortConfigIdType OBJECT-TYPE
          SYNTAX  INTEGER{
      		switchIp(0),
      		switchMac(1),
			switchUdf(2),
			switchUdfOnly(3)
      		}
          MAX-ACCESS  read-write
          STATUS  current
          DESCRIPTION
                  "0. switch IP:The switch's IP address will be used to encode the Circuit-ID option.
                   1. switch MAC:The switch's MAC address will be used to encode the Circuit-ID option.
				   2. switch UDF:The user specified string with the maximum length of 40 will be used to encode the Circuit-ID option.
				   3. switch UDF-ONLY:Only the user specified string with the maximum length of 40 will be used to encode the Circuit-ID option.
                   Select Circuit-ID type for the port."
          ::= { tpPppoeIdInsertionPortConfigEntry 3 }

      tpPppoeCircuitIdPortConfigUdfValue OBJECT-TYPE
          SYNTAX  OCTET STRING (SIZE (0..40))
		  MAX-ACCESS  read-create
		  STATUS  current
          DESCRIPTION
                  "A user specified string with the maximum length of 40. "
          ::= { tpPppoeIdInsertionPortConfigEntry 4 }

      tpPppoeRemoteIdPortConfigEnable OBJECT-TYPE
          SYNTAX  INTEGER{
      		disable(0),
      		enable(1)
      		}
          MAX-ACCESS  read-write
          STATUS  current
          DESCRIPTION
                  "0. disable
                   1. enable
                   Select Enable/Disable the PPPoE Remote-ID Insertion feature for the port."
          ::= { tpPppoeIdInsertionPortConfigEntry 5 }

      tpPppoeRemoteIdPortConfigValue OBJECT-TYPE
          SYNTAX  OCTET STRING (SIZE (0..40))
		  MAX-ACCESS  read-create
		  STATUS  current
          DESCRIPTION
                  "A user specified string with the maximum length of 40. "
          ::= { tpPppoeIdInsertionPortConfigEntry 6 }
END
