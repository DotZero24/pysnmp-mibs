TPLINK-VRRP-MIB DEFINITIONS ::= BEGIN

       IMPORTS
		OBJECT-TYPE,MODULE-IDENTITY,IpAddress

          	  	    FROM SNMPv2-SMI
	   TPRowStatus
				FROM TPLINK-TC-MIB

            tplinkMgmt
				FROM TPLINK-MIB;

	    tplinkVrrpMIB MODULE-IDENTITY
		LAST-UPDATED  "201212130000Z"
		ORGANIZATION  "TP-LINK"
		CONTACT-INFO  "www.tplink.com"
		DESCRIPTION
			 "This MIB describes objects used for managing Virtual Router
          Redundancy Protocol (VRRP) routers."

		REVISION    "201212130000Z"
		DESCRIPTION
			"Initial version of this MIB module."
		::= { tplinkMgmt 65 }

		tplinkVrrpMIBObjects		OBJECT IDENTIFIER	::= { tplinkVrrpMIB 1 }
		tplinkVrrpNotifications		OBJECT IDENTIFIER	::= { tplinkVrrpMIB 2 }


		tpVrrpGlobalCtrl		OBJECT IDENTIFIER ::= {tplinkVrrpMIBObjects 1}
		tpVrrpVirtualIpCtrl		OBJECT IDENTIFIER ::= {tplinkVrrpMIBObjects 2}
		tpVrrpTrackCtrl			OBJECT IDENTIFIER ::= {tplinkVrrpMIBObjects 3}
		tpVrrpStatistics		OBJECT IDENTIFIER ::= {tplinkVrrpMIBObjects 4}

-- *******************************************************************
--  VRRP Router Global Table
-- *******************************************************************

		tpVrrpGlobalCtrlTable OBJECT-TYPE
		  SYNTAX  SEQUENCE OF TpVrrpGlobalCtrlEntry
		  MAX-ACCESS  not-accessible
		  STATUS  current
		  DESCRIPTION
				  "Operations table for a VRRP router which consists of a
					sequence (i.e., one or more conceptual rows) of 'TpVrrpGlobalCtrlEntry' items."
		  ::= { tpVrrpGlobalCtrl 1 }

		tpVrrpGlobalCtrlEntry    OBJECT-TYPE
              SYNTAX  TpVrrpGlobalCtrlEntry
              MAX-ACCESS  not-accessible
              STATUS  current
              DESCRIPTION
                      "  An entry in the tpVrrpGlobalCtrlTable containing the operational
          characteristics of a virtual router. On a VRRP router,a given virtual router is identified by a combination
          of the VID and VRID.Rows in the table can be modified according to the tpVrrpStatus."
              INDEX   { tpVrrpVrid,tpVrrpVid }
              ::= { tpVrrpGlobalCtrlTable 1 }


		TpVrrpGlobalCtrlEntry  ::=
              SEQUENCE {
                  tpVrrpVrid
                    INTEGER,
                  tpVrrpVid
                  	INTEGER,
				  tpVrrpIntfStatus
				    INTEGER,
                  tpVrrpInterfaceIP
                  	IpAddress,
				  tpVrrpMacAddress
					OCTET STRING,
				  tpVrrpDescription
                    OCTET STRING,
				  tpVrrpPrimaryVirtualIp
					IpAddress,
				  tpVrrpRunPriority
					INTEGER,
				  tpVrrpConfigPriority
				    INTEGER,
				  tpVrrpAdvertisement
				    INTEGER,
				  tpVrrpPreeptMode
				    INTEGER,
				  tpVrrpTimeDelay
				    INTEGER,
				  tpVrrpAuthType
				    INTEGER,
				  tpVrrpKey
				    OCTET STRING,
				  tpVrrpState
				    INTEGER,
				  tpVrrpStatus
					TPRowStatus
              }
        tpVrrpVrid OBJECT-TYPE
              SYNTAX  INTEGER (1..255)
              MAX-ACCESS  read-only
              STATUS  current
              DESCRIPTION
                      "This object contains the Virtual Router Identifier (VRID)."
              ::= { tpVrrpGlobalCtrlEntry 1 }

		tpVrrpVid OBJECT-TYPE
              SYNTAX  INTEGER
              MAX-ACCESS  read-only
              STATUS  current
              DESCRIPTION
                      "The interface index"
              ::= { tpVrrpGlobalCtrlEntry 2 }

		tpVrrpIntfStatus OBJECT-TYPE
              SYNTAX   INTEGER {
								interfacevlan(1),     --VLAN interface
								routedport(0)     	  --RoutedPort interface

			  }
              MAX-ACCESS  read-only
              STATUS  current
              DESCRIPTION
                      "The interface status"
              ::= { tpVrrpGlobalCtrlEntry 3 }

		tpVrrpInterfaceIP OBJECT-TYPE
              SYNTAX   IpAddress
              MAX-ACCESS  read-only
              STATUS  current
              DESCRIPTION
                      "The interface IP address."
              ::= { tpVrrpGlobalCtrlEntry 4 }

		tpVrrpMacAddress OBJECT-TYPE
              SYNTAX   OCTET STRING
              MAX-ACCESS  read-only
              STATUS  current
              DESCRIPTION
                      "The virtual MAC address of the virtual router."
              ::= { tpVrrpGlobalCtrlEntry 5 }
		tpVrrpDescription OBJECT-TYPE
		  SYNTAX   OCTET STRING
		  MAX-ACCESS  read-create
		  STATUS  current
		  DESCRIPTION
				  "The description of  the VRRP."
		  ::= { tpVrrpGlobalCtrlEntry 6}

		 tpVrrpPrimaryVirtualIp OBJECT-TYPE
              SYNTAX   IpAddress
              MAX-ACCESS  read-only
              STATUS  current
              DESCRIPTION
                      "This is the IP address listed as the source in VRRP advertisement
         last received by this virtual router."
              ::= { tpVrrpGlobalCtrlEntry 7}

		tpVrrpRunPriority OBJECT-TYPE
              SYNTAX   INTEGER (1..255)
              MAX-ACCESS  read-only
              STATUS  current
              DESCRIPTION
                      "This object specifies the priority to be used for the
         virtual router master election process. Higher values imply
         higher priority.A priority of 255 is used for the router that owns the
         associated IP address(es)."
              ::= { tpVrrpGlobalCtrlEntry 8 }

		tpVrrpConfigPriority OBJECT-TYPE
              SYNTAX   INTEGER (1..255)
              MAX-ACCESS  read-create
              STATUS  current
              DESCRIPTION
                      "This object operate the priority to be used for the
         virtual router master election process."
              ::= { tpVrrpGlobalCtrlEntry 9}


		tpVrrpAdvertisement OBJECT-TYPE
              SYNTAX   INTEGER (1..255)
              MAX-ACCESS  read-create
              STATUS  current
              DESCRIPTION
                      "The time interval, in seconds, between sending
         advertisement messages. Only the master router sends
         VRRP advertisements."
              ::= { tpVrrpGlobalCtrlEntry 10}

		tpVrrpPreeptMode OBJECT-TYPE
              SYNTAX   INTEGER {
								enable(0),     --PreemptMode
								disable(1)     --NonPreemptMode

			  }
              MAX-ACCESS  read-create
              STATUS  current
              DESCRIPTION
                      "Controls whether a higher priority virtual router will
         preempt a lower priority master"
              ::= { tpVrrpGlobalCtrlEntry 11}

		tpVrrpTimeDelay  OBJECT-TYPE
              SYNTAX   INTEGER (1..255)
              MAX-ACCESS  read-create
              STATUS  current
              DESCRIPTION
                      "This is object is used to config the delay timer associated with the VRRP."
              ::= { tpVrrpGlobalCtrlEntry 12}
		tpVrrpAuthType  OBJECT-TYPE
              SYNTAX   INTEGER {
								normal(0),     --Normal
								simple(1),     --Simple
								md5(2)		   --MD5
			  }
              MAX-ACCESS  read-create
              STATUS  current
              DESCRIPTION
                      "Authentication type used for VRRP protocol exchanges between
         virtual routers. This value of this object is the same for a given ifindex(Vlan ID)."
              ::= { tpVrrpGlobalCtrlEntry 13}

		tpVrrpKey  OBJECT-TYPE
              SYNTAX   OCTET STRING
              MAX-ACCESS  read-create
              STATUS  current
              DESCRIPTION
                      "The Authentication Key. This object is set according to
         the value of the 'tpVrrpAuthType' object
         ('Simple' or 'MD5')."
              ::= { tpVrrpGlobalCtrlEntry 14 }

		tpVrrpState  OBJECT-TYPE
              SYNTAX    INTEGER {
						initialize(0),
						backup(1),
						master(2)
					}
              MAX-ACCESS  read-only
              STATUS  current
              DESCRIPTION
                      "The current state of the virtual router. This object has
         three defined values:

           - `initialize', which indicates that all the
             virtual router is waiting for a startup event.

           - `backup', which indicates the virtual router is
             monitoring the availability of the master router.

           - `master', which indicates that the virtual router
             is forwarding packets for IP addresses that are
             associated with this router."
              ::= { tpVrrpGlobalCtrlEntry 15 }
		tpVrrpStatus  OBJECT-TYPE
              SYNTAX   TPRowStatus
              MAX-ACCESS  read-create
              STATUS  current
              DESCRIPTION
                      "The following values are states:
                     these values may be used as follow:
                     active(1),if the entry is being used.
                     createAndGo(4),creat a new entry
                     destroy(6),destory the entry."
              ::= { tpVrrpGlobalCtrlEntry 16 }


-- *******************************************************************
--  VRRP Router virtual IP Table
-- *******************************************************************

		tpVrrpVirtualIpCtrlTable OBJECT-TYPE
		  SYNTAX  SEQUENCE OF TpVrrpVirtualIpCtrlEntry
		  MAX-ACCESS  not-accessible
		  STATUS  current
		  DESCRIPTION
				  "The table of addresses associated with this virtual router."
		  ::= { tpVrrpVirtualIpCtrl 1 }
		tpVrrpVirtualIpCtrlEntry    OBJECT-TYPE
              SYNTAX  TpVrrpVirtualIpCtrlEntry
              MAX-ACCESS  not-accessible
              STATUS  current
              DESCRIPTION
                      "   An entry in the table contains an IP address that is
         associated with a virtual router."
              INDEX   { tpVrrpVirtualIpVrid,tpVrrpVirtualIpVid,tpVrrpVirtualIpAddress}
              ::= { tpVrrpVirtualIpCtrlTable 1 }
		TpVrrpVirtualIpCtrlEntry  ::=
              SEQUENCE {
                  tpVrrpVirtualIpVrid
                    INTEGER,
                  tpVrrpVirtualIpVid
                  	INTEGER,
				  tpVrrpVirtualIpintfStatus
				    INTEGER,
                  tpVrrpVirtualIpAddress
                  	IpAddress,
				  tpVrrpVirtualIpStatus
					TPRowStatus
              }
		 tpVrrpVirtualIpVrid OBJECT-TYPE
              SYNTAX  INTEGER (1..255)
              MAX-ACCESS  read-only
              STATUS  current
              DESCRIPTION
                      "This object contains the Virtual Router Identifier (VRID)."
              ::= { tpVrrpVirtualIpCtrlEntry 1 }

		tpVrrpVirtualIpVid OBJECT-TYPE
              SYNTAX  INTEGER
              MAX-ACCESS  read-only
              STATUS  current
              DESCRIPTION
                      "The interface index"
              ::= { tpVrrpVirtualIpCtrlEntry 2 }
	    tpVrrpVirtualIpintfStatus OBJECT-TYPE
              SYNTAX   INTEGER {
								interfacevlan(1),     --VLAN interface
								routedport(0)     	  --RoutedPort interface

			  }
              MAX-ACCESS  read-only
              STATUS  current
              DESCRIPTION
                      "The interface status"
              ::= { tpVrrpVirtualIpCtrlEntry 3 }
		tpVrrpVirtualIpAddress OBJECT-TYPE
              SYNTAX  IpAddress
              MAX-ACCESS  read-only
              STATUS  current
              DESCRIPTION
                      "The virtual IP address associated with a virtual router. "
              ::= { tpVrrpVirtualIpCtrlEntry 4 }

		tpVrrpVirtualIpStatus OBJECT-TYPE
              SYNTAX  TPRowStatus
              MAX-ACCESS  read-create
              STATUS  current
              DESCRIPTION
                      "The following values are states:
                     these values may be used as follow:
                     active(1),if the entry is being used.
                     createAndGo(4),creat a new entry
                     destroy(6),destory the entry."
              ::= { tpVrrpVirtualIpCtrlEntry 5 }

-- *******************************************************************
--  VRRP Router track Table
-- *******************************************************************

		tpVrrpTrackCtrlTable OBJECT-TYPE
		  SYNTAX  SEQUENCE OF TpVrrpTrackCtrlEntry
		  MAX-ACCESS  not-accessible
		  STATUS  current
		  DESCRIPTION
				  "The table of ifindex tracked by the virtual router."
		  ::= { tpVrrpTrackCtrl 1 }

		tpVrrpTrackCtrlEntry    OBJECT-TYPE
              SYNTAX  TpVrrpTrackCtrlEntry
              MAX-ACCESS  not-accessible
              STATUS  current
              DESCRIPTION
                      " An entry in the table contains the ifindex and reduced priority that is
         associated with a virtual router.  "
              INDEX   { tpVrrpTrackVrid,tpVrrpTrackVid ,tpVrrpTrackInterface}
              ::= { tpVrrpTrackCtrlTable 1 }


		TpVrrpTrackCtrlEntry  ::=
              SEQUENCE {
                  tpVrrpTrackVrid
                    INTEGER,
                  tpVrrpTrackVid
                  	INTEGER,
				  tpVrrpTrackIntfStatus
				    INTEGER,
				  tpVrrpTrackInterface
					INTEGER,
				  tpVrrpTrackIntfTrackedStatus
				    INTEGER,
				  tpVrrpTrackPriortiy
				    INTEGER,
				  tpVrrpLinkState
					INTEGER,
				  tpVrrpTrackStatus
					TPRowStatus
              }
		 tpVrrpTrackVrid OBJECT-TYPE
              SYNTAX  INTEGER (1..255)
              MAX-ACCESS  read-only
              STATUS  current
              DESCRIPTION
                      "This object contains the Virtual Router Identifier (VRID)."
              ::= { tpVrrpTrackCtrlEntry 1 }
		tpVrrpTrackVid OBJECT-TYPE
              SYNTAX  INTEGER
              MAX-ACCESS  read-only
              STATUS  current
              DESCRIPTION
                      "The interface index"
              ::= { tpVrrpTrackCtrlEntry 2 }
	    tpVrrpTrackIntfStatus OBJECT-TYPE
              SYNTAX   INTEGER {
								interfacevlan(1),     --VLAN interface
								routedport(0)     	  --RoutedPort interface

			  }
              MAX-ACCESS  read-only
              STATUS  current
              DESCRIPTION
                      "The interface status"
              ::= { tpVrrpTrackCtrlEntry 3 }
		tpVrrpTrackInterface OBJECT-TYPE
				SYNTAX  INTEGER
				MAX-ACCESS  read-only
				STATUS  current
				DESCRIPTION
					  "The ifindex tracked by the virtual router."
				::= { tpVrrpTrackCtrlEntry 4 }
		tpVrrpTrackIntfTrackedStatus  OBJECT-TYPE
              SYNTAX   INTEGER {
								interfacevlan(1),     --VLAN interface
								routedport(0)     	  --RoutedPort interface

			  }
              MAX-ACCESS  read-only
              STATUS  current
              DESCRIPTION
                      "The interface status"
              ::= { tpVrrpTrackCtrlEntry 5 }
		tpVrrpTrackPriortiy OBJECT-TYPE
				SYNTAX  INTEGER (1..255)
				MAX-ACCESS  read-create
				STATUS  current
				DESCRIPTION
					  "The object operate the priority of the virtual router when the interface tracked linkdown."
				::= { tpVrrpTrackCtrlEntry 6 }
		tpVrrpLinkState OBJECT-TYPE
				SYNTAX  INTEGER {
							off(0),  --linkoff
							on(1)    --linkon
				}
				MAX-ACCESS  read-only
				STATUS  current
				DESCRIPTION
					  "The object display the status of the interface tracked ."
				::= { tpVrrpTrackCtrlEntry 7 }
		tpVrrpTrackStatus OBJECT-TYPE
              SYNTAX  TPRowStatus
              MAX-ACCESS  read-create
              STATUS  current
              DESCRIPTION
                      "The following values are states:
                     these values may be used as follow:
                     active(1),if the entry is being used.
                     createAndGo(4),creat a new entry
                     destroy(6),destory the entry."
              ::= { tpVrrpTrackCtrlEntry 8 }
-- *******************************************************************
--  VRRP Router Statistics
-- *******************************************************************

	tpVrrpChecksumErrors OBJECT-TYPE
     SYNTAX       INTEGER
     MAX-ACCESS   read-only
     STATUS       current
     DESCRIPTION
         "The total number of VRRP packets received with an invalid
         VRRP checksum value."
     ::= { tpVrrpStatistics 1 }

	tpVrrpVersionErrors OBJECT-TYPE
     SYNTAX       INTEGER
     MAX-ACCESS   read-only
     STATUS       current
     DESCRIPTION
         "The total number of VRRP packets received with an unknown
         or unsupported version number."
     ::= { tpVrrpStatistics 2 }

	tpVrrpVridErrors OBJECT-TYPE
     SYNTAX       INTEGER
     MAX-ACCESS   read-only
     STATUS       current
     DESCRIPTION
         "The total number of VRRP packets received with an invalid
         VRID for this virtual router."
     ::= { tpVrrpStatistics 3 }

	tpvrrpStatsClear OBJECT-TYPE
     SYNTAX       INTEGER {
								active(1),     --normal
								clear(0)       --setzero
			  }
     MAX-ACCESS   read-write
     STATUS       current
     DESCRIPTION
         "The following values are states:
          these values may be used as follow:
             active(1),if the entry is being used.
             clear(0),set the entry to 0."
     ::= { tpVrrpStatistics 5}


-- *******************************************************************
--  VRRP Router Statistics Table
-- *******************************************************************

	tpVrrpStatsTable OBJECT-TYPE
     SYNTAX       SEQUENCE OF TpVrrpStatsEntry
     MAX-ACCESS   not-accessible
     STATUS       current
     DESCRIPTION
         "Table of virtual router statistics."
     ::= { tpVrrpStatistics 4 }

	tpVrrpStatsEntry OBJECT-TYPE
     SYNTAX       TpVrrpStatsEntry
     MAX-ACCESS   not-accessible
     STATUS       current
     DESCRIPTION
         "An entry in the table, containing statistics information
         about a given virtual router."
     INDEX    { tpVrrpStatsVrid, tpVrrpStatsVid}
     ::= { tpVrrpStatsTable 1 }

 TpVrrpStatsEntry ::=
     SEQUENCE {
		 tpVrrpStatsVrid
			INTEGER,
		 tpVrrpStatsVid
			INTEGER,
		 tpVrrpStatsIntfStatus
		    INTEGER,
		 tpVrrpChecksumErr
			INTEGER,
		 tpVrrpVersionErr
			INTEGER,
         tpVrrpStatsBecomeMaster
             INTEGER,
         tpvrrpStatsAdvertiseRcvd
             INTEGER,
		 tpvrrpStatsAdvertiseSent
			INTEGER,
         tpvrrpStatsAdvertiseIntervalErrors
             INTEGER,
         tpvrrpStatsAuthFailures
             INTEGER,
         tpvrrpStatsIpTtlErrors
             INTEGER,
         tpvrrpStatsPriorityZeroPktsRcvd
             INTEGER,
         tpvrrpStatsPriorityZeroPktsSent
             INTEGER,
         tpvrrpStatsInvalidTypePktsRcvd
             INTEGER,
         tpvrrpStatsAddressListErrors
             INTEGER,
         tpvrrpStatsInvalidAuthType
             INTEGER,
         tpvrrpStatsAuthTypeMismatch
             INTEGER,
         tpvrrpStatsPacketLengthErrors
             INTEGER
     }

 tpVrrpStatsVrid  OBJECT-TYPE
	 SYNTAX       INTEGER
     MAX-ACCESS   read-only
     STATUS       current
     DESCRIPTION
         "the VRID of the virtual router. It is used together with interface ID to specify the virtual router to operate statistics."
     ::= { tpVrrpStatsEntry 1 }

 tpVrrpStatsVid 	OBJECT-TYPE
	 SYNTAX       INTEGER
     MAX-ACCESS   read-only
     STATUS       current
     DESCRIPTION
         "the interface ID of the virtual router. It is used together with VRID to specify the virtual router to operate statistics."
     ::= { tpVrrpStatsEntry 2 }
 tpVrrpStatsIntfStatus OBJECT-TYPE
              SYNTAX   INTEGER {
								interfacevlan(1),     --VLAN interface
								routedport(0)     	  --RoutedPort interface

			  }
              MAX-ACCESS  read-only
              STATUS  current
              DESCRIPTION
                      "The interface status"
              ::= { tpVrrpStatsEntry 3 }
 tpVrrpChecksumErr   OBJECT-TYPE
	 SYNTAX       INTEGER
     MAX-ACCESS   read-only
     STATUS       current
     DESCRIPTION
         "The total number of VRRP packets received with an invalid VRRP checksum value by this
         virtual router."
     ::= { tpVrrpStatsEntry 4 }
 tpVrrpVersionErr   OBJECT-TYPE
	 SYNTAX       INTEGER
     MAX-ACCESS   read-only
     STATUS       current
     DESCRIPTION
         "The total number of VRRP packets received with an unknown or unsupported version number by this
         virtual router."
     ::= { tpVrrpStatsEntry 5 }
 tpVrrpStatsBecomeMaster OBJECT-TYPE
     SYNTAX       INTEGER
     MAX-ACCESS   read-only
     STATUS       current
     DESCRIPTION
         "The total number of times that this virtual router's state
         has transitioned to MASTER."
     ::= { tpVrrpStatsEntry 6 }

 tpvrrpStatsAdvertiseRcvd OBJECT-TYPE
     SYNTAX       INTEGER
     MAX-ACCESS   read-only
     STATUS       current
     DESCRIPTION
         "The total number of VRRP advertisements received by this
         virtual router."
     ::= { tpVrrpStatsEntry 7}
 tpvrrpStatsAdvertiseSent OBJECT-TYPE
     SYNTAX       INTEGER
     MAX-ACCESS   read-only
     STATUS       current
     DESCRIPTION
         "The total number of VRRP advertisements sent by this
         virtual router."
     ::= { tpVrrpStatsEntry 8 }
 tpvrrpStatsAdvertiseIntervalErrors OBJECT-TYPE
     SYNTAX       INTEGER
     MAX-ACCESS   read-only
     STATUS       current
     DESCRIPTION
         "The total number of VRRP advertisement packets received
         for which the advertisement interval is different than the
         one configured for the local virtual router."
     ::= { tpVrrpStatsEntry 9}

 tpvrrpStatsAuthFailures OBJECT-TYPE
     SYNTAX       INTEGER
     MAX-ACCESS   read-only
     STATUS       current
     DESCRIPTION
         "The total number of VRRP packets received that do not pass
         the authentication check."
     ::= { tpVrrpStatsEntry 10 }

 tpvrrpStatsIpTtlErrors OBJECT-TYPE
     SYNTAX       INTEGER
     MAX-ACCESS   read-only
     STATUS       current
     DESCRIPTION
         "The total number of VRRP packets received by the virtual
         router with IP TTL (Time-To-Live) not equal to 255."
     ::= { tpVrrpStatsEntry 11 }

 tpvrrpStatsPriorityZeroPktsRcvd OBJECT-TYPE
     SYNTAX       INTEGER
     MAX-ACCESS   read-only
     STATUS       current
     DESCRIPTION
         "The total number of VRRP packets received by the virtual
         router with a priority of '0'."
     ::= { tpVrrpStatsEntry 12}

 tpvrrpStatsPriorityZeroPktsSent OBJECT-TYPE
     SYNTAX       INTEGER
     MAX-ACCESS   read-only
     STATUS       current
     DESCRIPTION
         "The total number of VRRP packets sent by the virtual router
         with a priority of '0'."
     ::= { tpVrrpStatsEntry 13 }

 tpvrrpStatsInvalidTypePktsRcvd OBJECT-TYPE
     SYNTAX       INTEGER
     MAX-ACCESS   read-only
     STATUS       current
     DESCRIPTION
         "The number of VRRP packets received by the virtual router
         with an invalid value in the 'type' field."
     ::= { tpVrrpStatsEntry 14}

 tpvrrpStatsAddressListErrors OBJECT-TYPE
     SYNTAX       INTEGER
     MAX-ACCESS   read-only
     STATUS       current
     DESCRIPTION
         "The total number of packets received for which the address
         list does not match the locally configured list for the
         virtual router."
     ::= { tpVrrpStatsEntry 15 }

 tpvrrpStatsInvalidAuthType OBJECT-TYPE
     SYNTAX       INTEGER
     MAX-ACCESS   read-only
     STATUS       current
     DESCRIPTION
         "The total number of packets received with an unknown
         authentication type."
     ::= { tpVrrpStatsEntry 16 }

 tpvrrpStatsAuthTypeMismatch OBJECT-TYPE
     SYNTAX       INTEGER
     MAX-ACCESS   read-only
     STATUS       current
     DESCRIPTION
         "The total number of packets received with 'Auth Type' not
         equal to the locally configured authentication method
         (`vrrpOperAuthType')."
     ::= { tpVrrpStatsEntry 17}

 tpvrrpStatsPacketLengthErrors OBJECT-TYPE
     SYNTAX       INTEGER
     MAX-ACCESS   read-only
     STATUS       current
     DESCRIPTION
         "The total number of packets received with a packet length
         less than the length of the VRRP header."
     ::= { tpVrrpStatsEntry 18 }


	END
