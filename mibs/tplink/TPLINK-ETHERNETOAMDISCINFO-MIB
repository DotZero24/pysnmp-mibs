TPLINK-ETHERNETOAMDISCINFO-MIB DEFINITIONS ::= BEGIN
		IMPORTS
			OBJECT-TYPE					FROM SNMPv2-SMI
	  		Counter						FROM RFC1155-SMI
			ethernetOamDiscoveryInfo	FROM TPLINK-ETHERNETOAM-MIB
			DisplayString
							FROM SNMPv2-TC
			ifIndex
							FROM RFC1213-MIB;

		ethernetOamDiscInfoTable OBJECT-TYPE
			SYNTAX SEQUENCE OF EthernetOamDiscInfoEntry
			MAX-ACCESS	not-accessible
			STATUS	current
			DESCRIPTION
			"A table that contains the discovery information of each port."
			::= {ethernetOamDiscoveryInfo 1}

		ethernetOamDiscInfoEntry OBJECT-TYPE
			SYNTAX EthernetOamDiscInfoEntry
			MAX-ACCESS	not-accessible
			STATUS	current
			DESCRIPTION
			"An entry that contains the discovery information of each port."
			INDEX {ifIndex}
			::= {ethernetOamDiscInfoTable 1}

		EthernetOamDiscInfoEntry ::=
		SEQUENCE
		{
			ethernetOamDiscInfoPort					DisplayString,
			ethernetOamDiscInfoLocOAM				INTEGER,
			ethernetOamDiscInfoLocMode				INTEGER,
			ethernetOamDiscInfoLocMaxOAMPDU			INTEGER,
			ethernetOamDiscInfoLocRemoteLoopback	INTEGER,
			ethernetOamDiscInfoLocUnidirection		INTEGER,
			ethernetOamDiscInfoLocLinkMonitoring	INTEGER,
			ethernetOamDiscInfoLocVariableRequest	INTEGER,
			ethernetOamDiscInfoLocPduRevision		INTEGER,
			ethernetOamDiscInfoLocOperationStatus	OCTET STRING(SIZE(0..25)),
			ethernetOamDiscInfoLocLoopbackStatus	OCTET STRING(SIZE(0..20)),
			ethernetOamDiscInfoRmtMode				INTEGER,
			ethernetOamDiscInfoRmtMacAddress		OCTET STRING(SIZE(0..18)),
			ethernetOamDiscInfoRmtVendorOUI			OCTET STRING(SIZE(0..7)),
			ethernetOamDiscInfoRmtMaxOAMPDU			INTEGER,
			ethernetOamDiscInfoRmtRemoteLoopback	INTEGER,
			ethernetOamDiscInfoRmtUnidirection		INTEGER,
			ethernetOamDiscInfoRmtLinkMonitoring	INTEGER,
			ethernetOamDiscInfoRmtVariableRequest	INTEGER,
			ethernetOamDiscInfoRmtPduRevision		INTEGER,
			ethernetOamDiscInfoRmtVendorInfo		OCTET STRING(SIZE(0..9))
		}

		ethernetOamDiscInfoPort OBJECT-TYPE
			SYNTAX DisplayString
			MAX-ACCESS	read-only
			STATUS	current
			DESCRIPTION
			"Displays the port number."
			::= {ethernetOamDiscInfoEntry 1}

		ethernetOamDiscInfoLocOAM OBJECT-TYPE
			SYNTAX INTEGER {disabled(0), enabled(1)}
			MAX-ACCESS	read-only
			STATUS	current
			DESCRIPTION
			"Displays the state of Ethernet OAM function."
			::= {ethernetOamDiscInfoEntry 2}

		ethernetOamDiscInfoLocMode OBJECT-TYPE
			SYNTAX INTEGER {passive(0),active(1)}
			MAX-ACCESS	read-only
			STATUS	current
			DESCRIPTION
			"Displays the mode of local Ethernet OAM client."
			::= {ethernetOamDiscInfoEntry 3}

		ethernetOamDiscInfoLocMaxOAMPDU OBJECT-TYPE
			SYNTAX INTEGER
			MAX-ACCESS	read-only
			STATUS	current
			DESCRIPTION
			"Displays the Maximum OAMPDU size of local Ethernet OAM client."
			::= {ethernetOamDiscInfoEntry 4}

		ethernetOamDiscInfoLocRemoteLoopback OBJECT-TYPE
			SYNTAX INTEGER {not-supported(0), supported(1)}
			MAX-ACCESS	read-only
			STATUS	current
			DESCRIPTION
			"Displays whether local Ethernet OAM client support remote loopback or not."
			::= {ethernetOamDiscInfoEntry 5}

		ethernetOamDiscInfoLocUnidirection OBJECT-TYPE
			SYNTAX INTEGER {not-supported(0), supported(1)}
			MAX-ACCESS	read-only
			STATUS	current
			DESCRIPTION
			"Displays whether local Ethernet OAM client support unidirection OAM operation or not."
			::= {ethernetOamDiscInfoEntry 6}

		ethernetOamDiscInfoLocLinkMonitoring OBJECT-TYPE
			SYNTAX INTEGER {not-supported(0), supported(1)}
			MAX-ACCESS	read-only
			STATUS	current
			DESCRIPTION
			"Displays whether local Ethernet OAM client support link monitoring or not."
			::= {ethernetOamDiscInfoEntry 7}

		ethernetOamDiscInfoLocVariableRequest OBJECT-TYPE
			SYNTAX INTEGER {not-supported(0), supported(1)}
			MAX-ACCESS	read-only
			STATUS	current
			DESCRIPTION
			"Displays whether local Ethernet OAM client support variable request or not."
			::= {ethernetOamDiscInfoEntry 8}

		ethernetOamDiscInfoLocPduRevision OBJECT-TYPE
			SYNTAX INTEGER
			MAX-ACCESS	read-only
			STATUS	current
			DESCRIPTION
			"Displays the current configuration revision of local Ethernet OAM client."
			::= {ethernetOamDiscInfoEntry 9}

		ethernetOamDiscInfoLocOperationStatus OBJECT-TYPE
			SYNTAX OCTET STRING(SIZE(0..25))
			MAX-ACCESS	read-only
			STATUS	current
			DESCRIPTION
			"Displays the operation status of local Ethernet OAM client."
			::= {ethernetOamDiscInfoEntry 10}

		ethernetOamDiscInfoLocLoopbackStatus OBJECT-TYPE
			SYNTAX OCTET STRING(SIZE(0..20))
			MAX-ACCESS	read-only
			STATUS	current
			DESCRIPTION
			"Displays the loopback status of local Ethernet OAM client."
			::= {ethernetOamDiscInfoEntry 11}

		ethernetOamDiscInfoRmtMode OBJECT-TYPE
			SYNTAX INTEGER {passive(0),active(1)}
			MAX-ACCESS	read-only
			STATUS	current
			DESCRIPTION
			"Displays the mode of remote Ethernet OAM client."
			::= {ethernetOamDiscInfoEntry 12}

		ethernetOamDiscInfoRmtMacAddress OBJECT-TYPE
			SYNTAX OCTET STRING(SIZE(0..18))
			MAX-ACCESS	read-only
			STATUS	current
			DESCRIPTION
			"Displays the MAC address of remote Ethernet OAM client."
			::= {ethernetOamDiscInfoEntry 13}

		ethernetOamDiscInfoRmtVendorOUI OBJECT-TYPE
			SYNTAX OCTET STRING(SIZE(0..7))
			MAX-ACCESS	read-only
			STATUS	current
			DESCRIPTION
			"Displays the vendor OUI of remote Ethernet OAM client."
			::= {ethernetOamDiscInfoEntry 14}

		ethernetOamDiscInfoRmtMaxOAMPDU OBJECT-TYPE
			SYNTAX INTEGER
			MAX-ACCESS	read-only
			STATUS	current
			DESCRIPTION
			"Displays the Maximum OAMPDU size of remote Ethernet OAM client."
			::= {ethernetOamDiscInfoEntry 15}

		ethernetOamDiscInfoRmtRemoteLoopback OBJECT-TYPE
			SYNTAX INTEGER {not-supported(0), supported(1)}
			MAX-ACCESS	read-only
			STATUS	current
			DESCRIPTION
			"Displays whether remote Ethernet OAM client support remote loopback or not."
			::= {ethernetOamDiscInfoEntry 16}

		ethernetOamDiscInfoRmtUnidirection OBJECT-TYPE
			SYNTAX INTEGER {not-supported(0), supported(1)}
			MAX-ACCESS	read-only
			STATUS	current
			DESCRIPTION
			"Displays whether remote Ethernet OAM client support unidirection OAM operation or not."
			::= {ethernetOamDiscInfoEntry 17}

		ethernetOamDiscInfoRmtLinkMonitoring OBJECT-TYPE
			SYNTAX INTEGER {not-supported(0), supported(1)}
			MAX-ACCESS	read-only
			STATUS	current
			DESCRIPTION
			"Displays whether remote Ethernet OAM client support link monitoring or not."
			::= {ethernetOamDiscInfoEntry 18}

		ethernetOamDiscInfoRmtVariableRequest OBJECT-TYPE
			SYNTAX INTEGER {not-supported(0), supported(1)}
			MAX-ACCESS	read-only
			STATUS	current
			DESCRIPTION
			"Displays whether remote Ethernet OAM client support variable request or not."
			::= {ethernetOamDiscInfoEntry 19}

		ethernetOamDiscInfoRmtPduRevision OBJECT-TYPE
			SYNTAX INTEGER
			MAX-ACCESS	read-only
			STATUS	current
			DESCRIPTION
			"Displays the current configuration revision of remote Ethernet OAM client."
			::= {ethernetOamDiscInfoEntry 20}

		ethernetOamDiscInfoRmtVendorInfo OBJECT-TYPE
			SYNTAX OCTET STRING(SIZE(0..9))
			MAX-ACCESS	read-only
			STATUS	current
			DESCRIPTION
			"Displays the vendor information of remote Ethernet OAM client."
			::= {ethernetOamDiscInfoEntry 21}

END
