F5OS-APPLIANCE-ALERT-NOTIF-MIB DEFINITIONS ::= BEGIN

IMPORTS
    MODULE-IDENTITY, NOTIFICATION-TYPE
        FROM SNMPv2-SMI
    NOTIFICATION-GROUP
        FROM SNMPv2-CONF
    f5Alerts, alertSource, alertEffect, alertSeverity,
    alertTimeStamp, alertDescription, f5AlertNotificationGroup
        FROM F5-ALERT-DEF-MIB
    ;

f5AlertNotification MODULE-IDENTITY
    LAST-UPDATED "201908040941Z"
    ORGANIZATION "F5 Networks, Inc."
    CONTACT-INFO
         "postal: F5 Networks, Inc.
                  801 5th Ave
                  Seattle,  WA 98104
          phone:  (206) 272-5555
          email:  support@f5.com"

    DESCRIPTION
        "Top-level infrastructure of the F5 Networks enterprise Alert MIB tree."

    REVISION       "201908040941Z"
    DESCRIPTION
        "F5 Alert Notification Types."

    ::= { f5Alerts 1 }

--=====================================================================--
-- F5 Alert Trap
--=====================================================================--

hardware-device-fault  NOTIFICATION-TYPE
    OBJECTS {
              alertSource,
              alertEffect,
              alertSeverity,
              alertTimeStamp,
              alertDescription
    }
    STATUS    current
    DESCRIPTION
        "Hardware device fault detected"
    ::= { f5AlertNotification 65536 }

firmware-fault  NOTIFICATION-TYPE
    OBJECTS {
              alertSource,
              alertEffect,
              alertSeverity,
              alertTimeStamp,
              alertDescription
    }
    STATUS    current
    DESCRIPTION
        "Firmware diagnostic state fault detected"
    ::= { f5AlertNotification 65537 }

unknown-alarm  NOTIFICATION-TYPE
    OBJECTS {
              alertSource,
              alertEffect,
              alertSeverity,
              alertTimeStamp,
              alertDescription
    }
    STATUS    current
    DESCRIPTION
        "Unregistered alarm detected"
    ::= { f5AlertNotification 65538 }

memory-fault  NOTIFICATION-TYPE
    OBJECTS {
              alertSource,
              alertEffect,
              alertSeverity,
              alertTimeStamp,
              alertDescription
    }
    STATUS    current
    DESCRIPTION
        "Fault in memory detected"
    ::= { f5AlertNotification 65539 }

drive-fault  NOTIFICATION-TYPE
    OBJECTS {
              alertSource,
              alertEffect,
              alertSeverity,
              alertTimeStamp,
              alertDescription
    }
    STATUS    current
    DESCRIPTION
        "Fault in drive detected"
    ::= { f5AlertNotification 65540 }

cpu-fault  NOTIFICATION-TYPE
    OBJECTS {
              alertSource,
              alertEffect,
              alertSeverity,
              alertTimeStamp,
              alertDescription
    }
    STATUS    current
    DESCRIPTION
        "CPU fault detected"
    ::= { f5AlertNotification 65541 }

pcie-fault  NOTIFICATION-TYPE
    OBJECTS {
              alertSource,
              alertEffect,
              alertSeverity,
              alertTimeStamp,
              alertDescription
    }
    STATUS    current
    DESCRIPTION
        "Fault in PCIe device detected"
    ::= { f5AlertNotification 65542 }

aom-fault  NOTIFICATION-TYPE
    OBJECTS {
              alertSource,
              alertEffect,
              alertSeverity,
              alertTimeStamp,
              alertDescription
    }
    STATUS    current
    DESCRIPTION
        "Fault detected in the AOM"
    ::= { f5AlertNotification 65543 }

drive-capacity-fault  NOTIFICATION-TYPE
    OBJECTS {
              alertSource,
              alertEffect,
              alertSeverity,
              alertTimeStamp,
              alertDescription
    }
    STATUS    current
    DESCRIPTION
        "Running out of drive capacity"
    ::= { f5AlertNotification 65544 }

power-fault  NOTIFICATION-TYPE
    OBJECTS {
              alertSource,
              alertEffect,
              alertSeverity,
              alertTimeStamp,
              alertDescription
    }
    STATUS    current
    DESCRIPTION
        "Power fault detected in hardware"
    ::= { f5AlertNotification 65545 }

thermal-fault  NOTIFICATION-TYPE
    OBJECTS {
              alertSource,
              alertEffect,
              alertSeverity,
              alertTimeStamp,
              alertDescription
    }
    STATUS    current
    DESCRIPTION
        "Thermal fault detected in hardware"
    ::= { f5AlertNotification 65546 }

drive-thermal-throttle  NOTIFICATION-TYPE
    OBJECTS {
              alertSource,
              alertEffect,
              alertSeverity,
              alertTimeStamp,
              alertDescription
    }
    STATUS    current
    DESCRIPTION
        "Drive has entered a thermal throttle condition"
    ::= { f5AlertNotification 65547 }

blade-thermal-fault  NOTIFICATION-TYPE
    OBJECTS {
              alertSource,
              alertEffect,
              alertSeverity,
              alertTimeStamp,
              alertDescription
    }
    STATUS    current
    DESCRIPTION
        "Thermal fault detected in blade"
    ::= { f5AlertNotification 65548 }

blade-hardware-fault  NOTIFICATION-TYPE
    OBJECTS {
              alertSource,
              alertEffect,
              alertSeverity,
              alertTimeStamp,
              alertDescription
    }
    STATUS    current
    DESCRIPTION
        "Hardware fault detected in blade"
    ::= { f5AlertNotification 65549 }

firmware-update-status  NOTIFICATION-TYPE
    OBJECTS {
              alertSource,
              alertEffect,
              alertSeverity,
              alertTimeStamp,
              alertDescription
    }
    STATUS    current
    DESCRIPTION
        "Firmware update status"
    ::= { f5AlertNotification 65550 }

drive-utilization  NOTIFICATION-TYPE
    OBJECTS {
              alertSource,
              alertEffect,
              alertSeverity,
              alertTimeStamp,
              alertDescription
    }
    STATUS    current
    DESCRIPTION
        "Drive utilization growth rate is high"
    ::= { f5AlertNotification 65551 }

service-health  NOTIFICATION-TYPE
    OBJECTS {
              alertSource,
              alertEffect,
              alertSeverity,
              alertTimeStamp,
              alertDescription
    }
    STATUS    current
    DESCRIPTION
        "Service health status"
    ::= { f5AlertNotification 65552 }

module-present  NOTIFICATION-TYPE
    OBJECTS {
              alertSource,
              alertEffect,
              alertSeverity,
              alertTimeStamp,
              alertDescription
    }
    STATUS    current
    DESCRIPTION
        "Change detected in appliance module presence"
    ::= { f5AlertNotification 66304 }

psu-fault  NOTIFICATION-TYPE
    OBJECTS {
              alertSource,
              alertEffect,
              alertSeverity,
              alertTimeStamp,
              alertDescription
    }
    STATUS    current
    DESCRIPTION
        "PSU fault detected"
    ::= { f5AlertNotification 66305 }

lcd-fault  NOTIFICATION-TYPE
    OBJECTS {
              alertSource,
              alertEffect,
              alertSeverity,
              alertTimeStamp,
              alertDescription
    }
    STATUS    current
    DESCRIPTION
        "Fault detected in LCD module"
    ::= { f5AlertNotification 66306 }

module-communication-error  NOTIFICATION-TYPE
    OBJECTS {
              alertSource,
              alertEffect,
              alertSeverity,
              alertTimeStamp,
              alertDescription
    }
    STATUS    current
    DESCRIPTION
        "Module communication error detected"
    ::= { f5AlertNotification 66307 }

fipsError  NOTIFICATION-TYPE
    OBJECTS {
              alertSource,
              alertEffect,
              alertSeverity,
              alertTimeStamp,
              alertDescription
    }
    STATUS    current
    DESCRIPTION
        "Crypto error identified in one or more services"
    ::= { f5AlertNotification 196608 }

core-dump  NOTIFICATION-TYPE
    OBJECTS {
              alertSource,
              alertEffect,
              alertSeverity,
              alertTimeStamp,
              alertDescription
    }
    STATUS    current
    DESCRIPTION
        "Detected process crash on the system"
    ::= { f5AlertNotification 327680 }

raidEvent  NOTIFICATION-TYPE
    OBJECTS {
              alertSource,
              alertEffect,
              alertSeverity,
              alertTimeStamp,
              alertDescription
    }
    STATUS    current
    DESCRIPTION
        "Notification of raid event"
    ::= { f5AlertNotification 393216 }

backplane  NOTIFICATION-TYPE
    OBJECTS {
              alertSource,
              alertEffect,
              alertSeverity,
              alertTimeStamp,
              alertDescription
    }
    STATUS    current
    DESCRIPTION
        "Could not establish backplane link with one or more system controllers"
    ::= { f5AlertNotification 262144 }

txPwrHiAlarm  NOTIFICATION-TYPE
    OBJECTS {
              alertSource,
              alertEffect,
              alertSeverity,
              alertTimeStamp,
              alertDescription
    }
    STATUS    current
    DESCRIPTION
        "Transmitter power high alarm"
    ::= { f5AlertNotification 262400 }

txPwrHiWarn  NOTIFICATION-TYPE
    OBJECTS {
              alertSource,
              alertEffect,
              alertSeverity,
              alertTimeStamp,
              alertDescription
    }
    STATUS    current
    DESCRIPTION
        "Transmitter power high warning"
    ::= { f5AlertNotification 262401 }

txPwrLoAlarm  NOTIFICATION-TYPE
    OBJECTS {
              alertSource,
              alertEffect,
              alertSeverity,
              alertTimeStamp,
              alertDescription
    }
    STATUS    current
    DESCRIPTION
        "Transmitter power low alarm"
    ::= { f5AlertNotification 262402 }

txPwrLoWarn  NOTIFICATION-TYPE
    OBJECTS {
              alertSource,
              alertEffect,
              alertSeverity,
              alertTimeStamp,
              alertDescription
    }
    STATUS    current
    DESCRIPTION
        "Transmitter power low warning"
    ::= { f5AlertNotification 262403 }

rxPwrHiAlarm  NOTIFICATION-TYPE
    OBJECTS {
              alertSource,
              alertEffect,
              alertSeverity,
              alertTimeStamp,
              alertDescription
    }
    STATUS    current
    DESCRIPTION
        "Receiver power high alarm"
    ::= { f5AlertNotification 262404 }

rxPwrHiWarn  NOTIFICATION-TYPE
    OBJECTS {
              alertSource,
              alertEffect,
              alertSeverity,
              alertTimeStamp,
              alertDescription
    }
    STATUS    current
    DESCRIPTION
        "Receiver power high warning"
    ::= { f5AlertNotification 262405 }

rxPwrLoAlarm  NOTIFICATION-TYPE
    OBJECTS {
              alertSource,
              alertEffect,
              alertSeverity,
              alertTimeStamp,
              alertDescription
    }
    STATUS    current
    DESCRIPTION
        "Receiver power low alarm"
    ::= { f5AlertNotification 262406 }

rxPwrLoWarn  NOTIFICATION-TYPE
    OBJECTS {
              alertSource,
              alertEffect,
              alertSeverity,
              alertTimeStamp,
              alertDescription
    }
    STATUS    current
    DESCRIPTION
        "Receiver power low warning"
    ::= { f5AlertNotification 262407 }

txBiasHiAlarm  NOTIFICATION-TYPE
    OBJECTS {
              alertSource,
              alertEffect,
              alertSeverity,
              alertTimeStamp,
              alertDescription
    }
    STATUS    current
    DESCRIPTION
        "Transmitter bias high alarm"
    ::= { f5AlertNotification 262408 }

txBiasHiWarn  NOTIFICATION-TYPE
    OBJECTS {
              alertSource,
              alertEffect,
              alertSeverity,
              alertTimeStamp,
              alertDescription
    }
    STATUS    current
    DESCRIPTION
        "Transmitter bias high warning"
    ::= { f5AlertNotification 262409 }

txBiasLoAlarm  NOTIFICATION-TYPE
    OBJECTS {
              alertSource,
              alertEffect,
              alertSeverity,
              alertTimeStamp,
              alertDescription
    }
    STATUS    current
    DESCRIPTION
        "Transmitter bias low alarm"
    ::= { f5AlertNotification 262410 }

txBiasLoWarn  NOTIFICATION-TYPE
    OBJECTS {
              alertSource,
              alertEffect,
              alertSeverity,
              alertTimeStamp,
              alertDescription
    }
    STATUS    current
    DESCRIPTION
        "Transmitter bias low warning"
    ::= { f5AlertNotification 262411 }

ddmTempHiAlarm  NOTIFICATION-TYPE
    OBJECTS {
              alertSource,
              alertEffect,
              alertSeverity,
              alertTimeStamp,
              alertDescription
    }
    STATUS    current
    DESCRIPTION
        "Optic temperature high alarm"
    ::= { f5AlertNotification 262412 }

ddmTempHiWarn  NOTIFICATION-TYPE
    OBJECTS {
              alertSource,
              alertEffect,
              alertSeverity,
              alertTimeStamp,
              alertDescription
    }
    STATUS    current
    DESCRIPTION
        "Optic temperature high warning"
    ::= { f5AlertNotification 262413 }

ddmTempLoAlarm  NOTIFICATION-TYPE
    OBJECTS {
              alertSource,
              alertEffect,
              alertSeverity,
              alertTimeStamp,
              alertDescription
    }
    STATUS    current
    DESCRIPTION
        "Optic temperature low alarm"
    ::= { f5AlertNotification 262414 }

ddmTempLoWarn  NOTIFICATION-TYPE
    OBJECTS {
              alertSource,
              alertEffect,
              alertSeverity,
              alertTimeStamp,
              alertDescription
    }
    STATUS    current
    DESCRIPTION
        "Optic temperature low warning"
    ::= { f5AlertNotification 262415 }

ddmVccHiAlarm  NOTIFICATION-TYPE
    OBJECTS {
              alertSource,
              alertEffect,
              alertSeverity,
              alertTimeStamp,
              alertDescription
    }
    STATUS    current
    DESCRIPTION
        "Optic voltage high alarm"
    ::= { f5AlertNotification 262416 }

ddmVccHiWarn  NOTIFICATION-TYPE
    OBJECTS {
              alertSource,
              alertEffect,
              alertSeverity,
              alertTimeStamp,
              alertDescription
    }
    STATUS    current
    DESCRIPTION
        "Optic voltage high warning"
    ::= { f5AlertNotification 262417 }

ddmVccLoAlarm  NOTIFICATION-TYPE
    OBJECTS {
              alertSource,
              alertEffect,
              alertSeverity,
              alertTimeStamp,
              alertDescription
    }
    STATUS    current
    DESCRIPTION
        "Optic voltage low alarm"
    ::= { f5AlertNotification 262418 }

ddmVccLoWarn  NOTIFICATION-TYPE
    OBJECTS {
              alertSource,
              alertEffect,
              alertSeverity,
              alertTimeStamp,
              alertDescription
    }
    STATUS    current
    DESCRIPTION
        "Optic voltage low warning"
    ::= { f5AlertNotification 262419 }

f5AlertsNotifyGroup  NOTIFICATION-GROUP
    NOTIFICATIONS {
        hardware-device-fault,
        firmware-fault,
        unknown-alarm,
        memory-fault,
        drive-fault,
        cpu-fault,
        pcie-fault,
        aom-fault,
        drive-capacity-fault,
        power-fault,
        thermal-fault,
        drive-thermal-throttle,
        blade-thermal-fault,
        blade-hardware-fault,
        firmware-update-status,
        drive-utilization,
        service-health,
        module-present,
        psu-fault,
        lcd-fault,
        module-communication-error,
        fipsError,
        core-dump,
        raidEvent,
        backplane,
        txPwrHiAlarm,
        txPwrHiWarn,
        txPwrLoAlarm,
        txPwrLoWarn,
        rxPwrHiAlarm,
        rxPwrHiWarn,
        rxPwrLoAlarm,
        rxPwrLoWarn,
        txBiasHiAlarm,
        txBiasHiWarn,
        txBiasLoAlarm,
        txBiasLoWarn,
        ddmTempHiAlarm,
        ddmTempHiWarn,
        ddmTempLoAlarm,
        ddmTempLoWarn,
        ddmVccHiAlarm,
        ddmVccHiWarn,
        ddmVccLoAlarm,
        ddmVccLoWarn
    }
    STATUS    current
    DESCRIPTION
       "The notifications related to the operation of the F5 System."
    ::= { f5AlertNotificationGroup 1 }

END
