F5-BIGIP-LOCAL-MIB DEFINITIONS ::= BEGIN
--================================================================
-- F5-BIGIP-LOCAL-MIB
--     A private enterprise MIB for F5 local traffic management
--     systems.
--     VERSION: 15.1.0.4
--================================================================

IMPORTS
    OBJECT-TYPE, NOTIFICATION-TYPE, MODULE-IDENTITY,
    Opaque, enterprises, Counter32, Counter64, TimeTicks
        FROM SNMPv2-SMI

    Gauge
        FROM RFC1155-SMI

    TEXTUAL-CONVENTION, MacAddress
        FROM SNMPv2-TC

    OBJECT-GROUP, MODULE-COMPLIANCE
        FROM SNMPv2-CONF

    InetAddress, InetAddressType, InetPortNumber
      FROM INET-ADDRESS-MIB

    bigipTrafficMgmt, bigipCompliances, bigipGroups, LongDisplayString
      FROM F5-BIGIP-COMMON-MIB;

--================================================================
bigipLocalTM MODULE-IDENTITY
    LAST-UPDATED "202004142103Z" -- Tue Apr 14 21:03:10 UTC 2020
    ORGANIZATION "F5 Networks, Inc."
    CONTACT-INFO
         "postal: F5 Networks, Inc.
	 	  401 Elliott Ave. West
                  Seattle, WA 98119
          phone:  (206) 272-5555
          email:  support@f5.com"

    DESCRIPTION
        "Top-level infrastructure of the F5 enterprise MIB tree."
    ::= { bigipTrafficMgmt 2 }

--================================================================

-- bigipLocalTM
ltmGlobals             OBJECT IDENTIFIER ::= { bigipLocalTM 1 }
ltmMirrors             OBJECT IDENTIFIER ::= { bigipLocalTM 2 }
ltmNATs                OBJECT IDENTIFIER ::= { bigipLocalTM 3 }
ltmNodes               OBJECT IDENTIFIER ::= { bigipLocalTM 4 }
ltmPools               OBJECT IDENTIFIER ::= { bigipLocalTM 5 }
ltmProfiles            OBJECT IDENTIFIER ::= { bigipLocalTM 6 }
ltmRateFilters         OBJECT IDENTIFIER ::= { bigipLocalTM 7 }
ltmRules               OBJECT IDENTIFIER ::= { bigipLocalTM 8 }
ltmSNATs               OBJECT IDENTIFIER ::= { bigipLocalTM 9 }
ltmVirtualServers      OBJECT IDENTIFIER ::= { bigipLocalTM 10 }
ltmRst                 OBJECT IDENTIFIER ::= { bigipLocalTM 11 }
ltmDNS                 OBJECT IDENTIFIER ::= { bigipLocalTM 12 }
ltmBWC                 OBJECT IDENTIFIER ::= { bigipLocalTM 13 }
ltmLSNs                OBJECT IDENTIFIER ::= { bigipLocalTM 14 }
ltmRouteDomains        OBJECT IDENTIFIER ::= { bigipLocalTM 15 }
ltmPolicies            OBJECT IDENTIFIER ::= { bigipLocalTM 16 }
ltmOCSPStapling        OBJECT IDENTIFIER ::= { bigipLocalTM 17 }
ltmFwNATs              OBJECT IDENTIFIER ::= { bigipLocalTM 18 }

--ltmGlobals
ltmGlobalAttr           OBJECT IDENTIFIER ::= { ltmGlobals 1 }
ltmDosAttackDataStat    OBJECT IDENTIFIER ::= { ltmGlobals 2 }
ltmFwAdminIpRuleStat    OBJECT IDENTIFIER ::= { ltmGlobals 3 }
ltmFwIpintGlobalStat    OBJECT IDENTIFIER ::= { ltmGlobals 4 }
ltmFwRuleStat           OBJECT IDENTIFIER ::= { ltmGlobals 5 }
ltmFwContextStat        OBJECT IDENTIFIER ::= { ltmGlobals 6 }

--ltmMirrors
ltmMirrorPort           OBJECT IDENTIFIER ::= { ltmMirrors 1 }
ltmMirrorPortMember     OBJECT IDENTIFIER ::= { ltmMirrors 2 }

--ltmNATs
ltmNat                  OBJECT IDENTIFIER ::= { ltmNATs 1 }
ltmNatStat              OBJECT IDENTIFIER ::= { ltmNATs 2 }
ltmNatVlan              OBJECT IDENTIFIER ::= { ltmNATs 3 }

--ltmNodes
ltmNodeAddr             OBJECT IDENTIFIER ::= { ltmNodes 1 }
ltmNodeAddrStat         OBJECT IDENTIFIER ::= { ltmNodes 2 }
ltmNodeAddrStatus       OBJECT IDENTIFIER ::= { ltmNodes 3 }

--ltmPools
ltmPool                 OBJECT IDENTIFIER ::= { ltmPools 1 }
ltmPoolStat             OBJECT IDENTIFIER ::= { ltmPools 2 }
ltmPoolMember           OBJECT IDENTIFIER ::= { ltmPools 3 }
ltmPoolMemberStat       OBJECT IDENTIFIER ::= { ltmPools 4 }
ltmPoolStatus           OBJECT IDENTIFIER ::= { ltmPools 5 }
ltmPoolMemberStatus     OBJECT IDENTIFIER ::= { ltmPools 6 }

--ltmProfiles
ltmAuth                 OBJECT IDENTIFIER ::= { ltmProfiles 1 }
ltmClientSsl            OBJECT IDENTIFIER ::= { ltmProfiles 2 }
ltmServerSsl            OBJECT IDENTIFIER ::= { ltmProfiles 3 }
ltmConnPool             OBJECT IDENTIFIER ::= { ltmProfiles 4 }
ltmFastL4               OBJECT IDENTIFIER ::= { ltmProfiles 5 }
ltmFtp                  OBJECT IDENTIFIER ::= { ltmProfiles 6 }
ltmHttp                 OBJECT IDENTIFIER ::= { ltmProfiles 7 }
ltmPersist              OBJECT IDENTIFIER ::= { ltmProfiles 8 }
ltmStream               OBJECT IDENTIFIER ::= { ltmProfiles 9 }
ltmTcp                  OBJECT IDENTIFIER ::= { ltmProfiles 10 }
ltmUdp                  OBJECT IDENTIFIER ::= { ltmProfiles 11 }
ltmFastHttp             OBJECT IDENTIFIER ::= { ltmProfiles 12 }
ltmXml                  OBJECT IDENTIFIER ::= { ltmProfiles 13 }
ltmDns                  OBJECT IDENTIFIER ::= { ltmProfiles 14 }
ltmHttpClass            OBJECT IDENTIFIER ::= { ltmProfiles 15 }
ltmIiop                 OBJECT IDENTIFIER ::= { ltmProfiles 16 }
ltmRtsp                 OBJECT IDENTIFIER ::= { ltmProfiles 17 }
ltmSctp                 OBJECT IDENTIFIER ::= { ltmProfiles 18 }
ltmUserStat             OBJECT IDENTIFIER ::= { ltmProfiles 19 }
ltmSip                  OBJECT IDENTIFIER ::= { ltmProfiles 20 }
ltmIsession             OBJECT IDENTIFIER ::= { ltmProfiles 21 }
ltmHttpCompression      OBJECT IDENTIFIER ::= { ltmProfiles 22 }
ltmWebAcceleration      OBJECT IDENTIFIER ::= { ltmProfiles 23 }
ltmDos                  OBJECT IDENTIFIER ::= { ltmProfiles 24 }
ltmSpdy                 OBJECT IDENTIFIER ::= { ltmProfiles 25 }
ltmV6rd                 OBJECT IDENTIFIER ::= { ltmProfiles 26 }
ltmPptp                 OBJECT IDENTIFIER ::= { ltmProfiles 27 }
ltmPcp                  OBJECT IDENTIFIER ::= { ltmProfiles 28 }
ltmAlgLog               OBJECT IDENTIFIER ::= { ltmProfiles 29 }
ltmLsnLog               OBJECT IDENTIFIER ::= { ltmProfiles 30 }
ltmTftp                 OBJECT IDENTIFIER ::= { ltmProfiles 31 }
ltmHttp2                OBJECT IDENTIFIER ::= { ltmProfiles 32 }
ltmWebsocket            OBJECT IDENTIFIER ::= { ltmProfiles 33 }
ltmTcpanalytics         OBJECT IDENTIFIER ::= { ltmProfiles 34 }
ltmIpsecalg             OBJECT IDENTIFIER ::= { ltmProfiles 35 }
ltmSplitsessionclient   OBJECT IDENTIFIER ::= { ltmProfiles 36 }
ltmSplitsessionserver   OBJECT IDENTIFIER ::= { ltmProfiles 37 }
ltmHttpProxyConnect     OBJECT IDENTIFIER ::= { ltmProfiles 38 }
ltmDiametersession      OBJECT IDENTIFIER ::= { ltmProfiles 39 }
ltmDiameterrouter       OBJECT IDENTIFIER ::= { ltmProfiles 40 }
ltmMrPmbrDiameter       OBJECT IDENTIFIER ::= { ltmProfiles 41 }
ltmSipsession           OBJECT IDENTIFIER ::= { ltmProfiles 42 }
ltmSiprouter            OBJECT IDENTIFIER ::= { ltmProfiles 43 }
ltmMrPmbrSip            OBJECT IDENTIFIER ::= { ltmProfiles 44 }


--ltmAuth
ltmAuthProfile          OBJECT IDENTIFIER ::= { ltmAuth 1 }
ltmAuthProfileStat      OBJECT IDENTIFIER ::= { ltmAuth 2 }

--ltmClientSsl
ltmClientSslProfile     OBJECT IDENTIFIER ::= { ltmClientSsl 1 }
ltmClientSslProfileStat OBJECT IDENTIFIER ::= { ltmClientSsl 2 }
ltmClientSslCertKeyChain OBJECT IDENTIFIER ::= { ltmClientSsl 3 }

--ltmServerSsl
ltmServerSslProfile     OBJECT IDENTIFIER ::= { ltmServerSsl 1 }
ltmServerSslProfileStat OBJECT IDENTIFIER ::= { ltmServerSsl 2 }
ltmServerSslProfileC3dCertExtensionCustomOids OBJECT IDENTIFIER ::= { ltmServerSsl 3 }

--ltmConnPool
ltmConnPoolProfile      OBJECT IDENTIFIER ::= { ltmConnPool 1 }
ltmConnPoolProfileStat  OBJECT IDENTIFIER ::= { ltmConnPool 2 }

--ltmFastL4
ltmFastL4Profile        OBJECT IDENTIFIER ::= { ltmFastL4 1 }
ltmFastL4ProfileStat    OBJECT IDENTIFIER ::= { ltmFastL4 2 }

--ltmFtp
ltmFtpProfile           OBJECT IDENTIFIER ::= { ltmFtp 1 }
ltmFtpProfileStat       OBJECT IDENTIFIER ::= { ltmFtp 2 }

--ltmHttp
ltmHttpProfile                    OBJECT IDENTIFIER ::= { ltmHttp 1 }
ltmHttpProfileCompUriIncl         OBJECT IDENTIFIER ::= { ltmHttp 2 }
ltmHttpProfileCompUriExcl         OBJECT IDENTIFIER ::= { ltmHttp 3 }
ltmHttpProfileCompContTypeIncl    OBJECT IDENTIFIER ::= { ltmHttp 4 }
ltmHttpProfileCompContTypeExcl    OBJECT IDENTIFIER ::= { ltmHttp 5 }
ltmHttpProfileStat                OBJECT IDENTIFIER ::= { ltmHttp 6 }
ltmHttpProfileRamUriExcl          OBJECT IDENTIFIER ::= { ltmHttp 7 }
ltmHttpProfileRamUriIncl          OBJECT IDENTIFIER ::= { ltmHttp 8 }
ltmHttpProfileRamUriPin           OBJECT IDENTIFIER ::= { ltmHttp 9 }
ltmHttpProfileFallbackStatus      OBJECT IDENTIFIER ::= { ltmHttp 10 }
ltmHttpProfileRespHeadersPerm     OBJECT IDENTIFIER ::= { ltmHttp 11 }
ltmHttpProfileEncCookies          OBJECT IDENTIFIER ::= { ltmHttp 12 }
ltmHttpProfileKnownMethods        OBJECT IDENTIFIER ::= { ltmHttp 13 }

--ltmPersist
ltmPersistProfile       OBJECT IDENTIFIER ::= { ltmPersist 1 }

--ltmStream
ltmStreamProfile        OBJECT IDENTIFIER ::= { ltmStream 1 }
ltmStreamProfileStat    OBJECT IDENTIFIER ::= { ltmStream 2 }

--ltmTcp
ltmTcpProfile           OBJECT IDENTIFIER ::= { ltmTcp 1 }
ltmTcpProfileStat       OBJECT IDENTIFIER ::= { ltmTcp 2 }

--ltmUdp
ltmUdpProfile           OBJECT IDENTIFIER ::= { ltmUdp 1 }
ltmUdpProfileStat       OBJECT IDENTIFIER ::= { ltmUdp 2 }

--ltmFastHttp
ltmFastHttpProfile      OBJECT IDENTIFIER ::= { ltmFastHttp 1 }
ltmFastHttpProfileStat  OBJECT IDENTIFIER ::= { ltmFastHttp 2 }

--ltmXml
ltmXmlProfile           OBJECT IDENTIFIER ::= { ltmXml 1 }
ltmXmlProfileStat       OBJECT IDENTIFIER ::= { ltmXml 2 }
ltmXmlProfileXpathQueries      OBJECT IDENTIFIER ::= { ltmXml 3 }
ltmXmlProfileNamespaceMappings      OBJECT IDENTIFIER ::= { ltmXml 4 }

--ltmHttpClass
ltmHttpClassProfile     OBJECT IDENTIFIER ::= { ltmHttpClass 1 }
ltmHttpClassProfileHost OBJECT IDENTIFIER ::= { ltmHttpClass 2 }
ltmHttpClassProfileUri  OBJECT IDENTIFIER ::= { ltmHttpClass 3 }
ltmHttpClassProfileHead OBJECT IDENTIFIER ::= { ltmHttpClass 4 }
ltmHttpClassProfileCook OBJECT IDENTIFIER ::= { ltmHttpClass 5 }
ltmHttpClassProfileStat OBJECT IDENTIFIER ::= { ltmHttpClass 6 }

--ltmIiop
ltmIiopProfile          OBJECT IDENTIFIER ::= { ltmIiop 1 }
ltmIiopProfileStat      OBJECT IDENTIFIER ::= { ltmIiop 2 }

--ltmRtsp
ltmRtspProfile          OBJECT IDENTIFIER ::= { ltmRtsp 1 }
ltmRtspProfileStat      OBJECT IDENTIFIER ::= { ltmRtsp 2 }

--ltmSctp
ltmSctpProfile          OBJECT IDENTIFIER ::= { ltmSctp 1 }
ltmSctpProfileStat      OBJECT IDENTIFIER ::= { ltmSctp 2 }

--ltmUserStat
ltmUserStatProfile      OBJECT IDENTIFIER ::= { ltmUserStat 1 }
ltmUserStatProfileStat  OBJECT IDENTIFIER ::= { ltmUserStat 2 }

--ltmSip
ltmSipProfile           OBJECT IDENTIFIER ::= { ltmSip 1 }
ltmSipProfileStat       OBJECT IDENTIFIER ::= { ltmSip 2 }

--ltmIsession
ltmIsessionProfile      OBJECT IDENTIFIER ::= { ltmIsession 1 }
ltmIsessionProfileStat  OBJECT IDENTIFIER ::= { ltmIsession 2 }

--ltmHttpCompression
ltmHttpCompressionProfile         OBJECT IDENTIFIER ::= { ltmHttpCompression 1 }
ltmHttpCompressionProfileUriIncl  OBJECT IDENTIFIER ::= { ltmHttpCompression 2 }
ltmHttpCompressionProfileUriExcl  OBJECT IDENTIFIER ::= { ltmHttpCompression 3 }
ltmHttpCompressionProfileContTypeIncl OBJECT IDENTIFIER ::= { ltmHttpCompression 4 }
ltmHttpCompressionProfileContTypeExcl OBJECT IDENTIFIER ::= { ltmHttpCompression 5 }
ltmHttpCompressionProfileStat     OBJECT IDENTIFIER ::= { ltmHttpCompression 6 }

--ltmWebAcceleration
ltmWebAccelerationProfile         OBJECT IDENTIFIER ::= { ltmWebAcceleration 1 }
ltmWebAccelerationProfileUriExcl  OBJECT IDENTIFIER ::= { ltmWebAcceleration 2 }
ltmWebAccelerationProfileUriIncl  OBJECT IDENTIFIER ::= { ltmWebAcceleration 3 }
ltmWebAccelerationProfileUriPin   OBJECT IDENTIFIER ::= { ltmWebAcceleration 4 }
ltmWebAccelerationProfileStat     OBJECT IDENTIFIER ::= { ltmWebAcceleration 5 }
ltmWebAccelerationProfileUriOver  OBJECT IDENTIFIER ::= { ltmWebAcceleration 6 }

--ltmDns
ltmDnsProfile           OBJECT IDENTIFIER ::= { ltmDns 1 }
ltmDnsProfileStat       OBJECT IDENTIFIER ::= { ltmDns 2 }

--ltmDos
ltmDosProfile           OBJECT IDENTIFIER ::= { ltmDos 1 }
ltmDosApplication       OBJECT IDENTIFIER ::= { ltmDos 2 }
ltmDosWhiteIp           OBJECT IDENTIFIER ::= { ltmDos 3 }
ltmDosApplicationHeavyUrlIncl OBJECT IDENTIFIER ::= { ltmDos 4 }
ltmDosApplicationHeavyUrlExcl OBJECT IDENTIFIER ::= { ltmDos 5 }

--ltmRateFilters
ltmRateFilter           OBJECT IDENTIFIER ::= { ltmRateFilters 1 }
ltmRateFilterStat       OBJECT IDENTIFIER ::= { ltmRateFilters 2 }

--ltmRules
ltmRule                 OBJECT IDENTIFIER ::= { ltmRules 1 }
ltmRuleEvent            OBJECT IDENTIFIER ::= { ltmRules 2 }
ltmRuleEventStat        OBJECT IDENTIFIER ::= { ltmRules 3 }

--ltmSNATs
ltmSnat                 OBJECT IDENTIFIER ::= { ltmSNATs 1 }
ltmSnatStat             OBJECT IDENTIFIER ::= { ltmSNATs 2 }
ltmSnatVlan             OBJECT IDENTIFIER ::= { ltmSNATs 3 }
ltmSnatOrigAddr         OBJECT IDENTIFIER ::= { ltmSNATs 4 }
ltmTransAddr            OBJECT IDENTIFIER ::= { ltmSNATs 5 }
ltmTransAddrStat        OBJECT IDENTIFIER ::= { ltmSNATs 6 }
ltmSnatPool             OBJECT IDENTIFIER ::= { ltmSNATs 7 }
ltmSnatPoolStat         OBJECT IDENTIFIER ::= { ltmSNATs 8 }
ltmSnatpoolTransAddr    OBJECT IDENTIFIER ::= { ltmSNATs 9 }

--ltmVirtualServers
ltmVirtualServ          OBJECT IDENTIFIER ::= { ltmVirtualServers 1 }
ltmVirtualServStat      OBJECT IDENTIFIER ::= { ltmVirtualServers 2 }
ltmVirtualServAuth      OBJECT IDENTIFIER ::= { ltmVirtualServers 3 }
ltmVirtualServPersist   OBJECT IDENTIFIER ::= { ltmVirtualServers 4 }
ltmVirtualServProfile   OBJECT IDENTIFIER ::= { ltmVirtualServers 5 }
ltmVirtualServPool      OBJECT IDENTIFIER ::= { ltmVirtualServers 6 }
ltmVirtualServClonePool OBJECT IDENTIFIER ::= { ltmVirtualServers 7 }
ltmVirtualServRule      OBJECT IDENTIFIER ::= { ltmVirtualServers 8 }
ltmVirtualServVlan      OBJECT IDENTIFIER ::= { ltmVirtualServers 9 }
ltmVirtualAddr          OBJECT IDENTIFIER ::= { ltmVirtualServers 10 }
ltmVirtualAddrStat      OBJECT IDENTIFIER ::= { ltmVirtualServers 11 }
ltmVirtualServHttpClass OBJECT IDENTIFIER ::= { ltmVirtualServers 12 }
ltmVirtualServStatus    OBJECT IDENTIFIER ::= { ltmVirtualServers 13 }
ltmVirtualAddrStatus    OBJECT IDENTIFIER ::= { ltmVirtualServers 14 }
ltmVirtualModuleScore   OBJECT IDENTIFIER ::= { ltmVirtualServers 15 }
ltmNetworkAttackDataStat     OBJECT IDENTIFIER ::= { ltmVirtualServers 16 }
ltmFwIpintVirtualStat   OBJECT IDENTIFIER ::= { ltmVirtualServers 17 }

--ltmRst
ltmRstCauseStat         OBJECT IDENTIFIER ::= { ltmRst 1 }

--ltmDNS
ltmDnsCache                          OBJECT IDENTIFIER ::= { ltmDNS 1 }
ltmDnsCacheStat                      OBJECT IDENTIFIER ::= { ltmDNS 2 }
ltmDnsSecurity                       OBJECT IDENTIFIER ::= { ltmDNS 3 }
ltmDnsSecurityStat                   OBJECT IDENTIFIER ::= { ltmDNS 4 }
ltmDnsQueryFilter                    OBJECT IDENTIFIER ::= { ltmDNS 5 }
ltmDnsHeaderFilter                   OBJECT IDENTIFIER ::= { ltmDNS 6 }
ltmDnsExpressStat                    OBJECT IDENTIFIER ::= { ltmDNS 7 }
ltmDnsServerStat                     OBJECT IDENTIFIER ::= { ltmDNS 8 }
ltmDnsCacheForwardZone               OBJECT IDENTIFIER ::= { ltmDNS 9 }
ltmDnsCacheForwardZoneNameServer     OBJECT IDENTIFIER ::= { ltmDNS 10 }

--ltmBWC
ltmBwcPolicyStat        OBJECT IDENTIFIER ::= { ltmBWC 1 }

--ltmLSNs
ltmLsnPrefix                 OBJECT IDENTIFIER ::= { ltmLSNs 1 }
ltmLsnPool                   OBJECT IDENTIFIER ::= { ltmLSNs 2 }
ltmLsnPrefixLsnPool          OBJECT IDENTIFIER ::= { ltmLSNs 3 }
ltmLsnPrefixLsnPoolBackup    OBJECT IDENTIFIER ::= { ltmLSNs 4 }
ltmLsnPoolVlan               OBJECT IDENTIFIER ::= { ltmLSNs 5 }
ltmLsnPoolStat               OBJECT IDENTIFIER ::= { ltmLSNs 6 }
ltmLsnPoolFailureStat        OBJECT IDENTIFIER ::= { ltmLSNs 7 }

--ltmFwNATs
ltmFwNatDynamicPool              OBJECT IDENTIFIER ::= { ltmFwNATs 1 }
ltmFwNatDynamicPoolStat          OBJECT IDENTIFIER ::= { ltmFwNATs 2 }
ltmFwNatDynamicPoolFailureStat   OBJECT IDENTIFIER ::= { ltmFwNATs 3 }
ltmFwNatStaticSourceTranslationPool           OBJECT IDENTIFIER ::= { ltmFwNATs 4 }
ltmFwNatStaticSourceTranslationPoolStat       OBJECT IDENTIFIER ::= { ltmFwNATs 5 }
ltmFwNatStaticDestinationTranslationPool      OBJECT IDENTIFIER ::= { ltmFwNATs 6 }
ltmFwNatStaticDestinationTranslationPoolStat  OBJECT IDENTIFIER ::= { ltmFwNATs 7 }


--ltmSpdy
ltmSpdyProfile                  OBJECT IDENTIFIER ::= { ltmSpdy 1 }
ltmSpdyProfileProtocolVersions  OBJECT IDENTIFIER ::= { ltmSpdy 2 }
ltmSpdyProfileStat              OBJECT IDENTIFIER ::= { ltmSpdy 3 }

--ltmV6rd
ltmV6rdProfile                  OBJECT IDENTIFIER ::= { ltmV6rd 1 }

--ltmPptp
ltmPptpProfile                  OBJECT IDENTIFIER ::= { ltmPptp 1 }
ltmPptpProfileStat              OBJECT IDENTIFIER ::= { ltmPptp 2 }

--ltmPcp
ltmPcpPrefix                   OBJECT IDENTIFIER ::= { ltmPcp  1 }
ltmPcpProfile                  OBJECT IDENTIFIER ::= { ltmPcp  2 }
ltmPcpPrefixProfilePcp         OBJECT IDENTIFIER ::= { ltmPcp  3 }
ltmPcpProfileStat              OBJECT IDENTIFIER ::= { ltmPcp  4 }

--ltmRouteDomains
ltmFwIpintRouteDomainStat      OBJECT IDENTIFIER ::= { ltmRouteDomains 1 }
ltmRouteDomainStat             OBJECT IDENTIFIER ::= { ltmRouteDomains 2 }

--ltmPolicies
ltmFlowEvictionPolicyStat      OBJECT IDENTIFIER ::= { ltmPolicies 1 }
ltmFwPolicyRuleStat            OBJECT IDENTIFIER ::= { ltmPolicies 2 }

--ltmAlgLog
ltmAlgLogProfile                             OBJECT IDENTIFIER ::= { ltmAlgLog 1 }
ltmAlgLogProfileStartControlElements         OBJECT IDENTIFIER ::= { ltmAlgLog 2 }
ltmAlgLogProfileEndControlElements           OBJECT IDENTIFIER ::= { ltmAlgLog 3 }
ltmAlgLogProfileStartDataElements            OBJECT IDENTIFIER ::= { ltmAlgLog 4 }
ltmAlgLogProfileEndDataElements              OBJECT IDENTIFIER ::= { ltmAlgLog 5 }

--ltmLsnLog
ltmLsnLogProfile                             OBJECT IDENTIFIER ::= { ltmLsnLog 1 }
ltmLsnLogProfileStartOutboundElements        OBJECT IDENTIFIER ::= { ltmLsnLog 2 }
ltmLsnLogProfileEndOutboundElements          OBJECT IDENTIFIER ::= { ltmLsnLog 3 }

--ltmOCSPStapling
ltmOcspStaplingParameters                    OBJECT IDENTIFIER ::= { ltmOCSPStapling 1 }

--ltmTftp
ltmTftpProfile          OBJECT IDENTIFIER ::= { ltmTftp 1 }
ltmTftpProfileStat      OBJECT IDENTIFIER ::= { ltmTftp 2 }

--ltmIpsecalg
ltmIpsecalgProfile                           OBJECT IDENTIFIER ::= { ltmIpsecalg 1 }
ltmIpsecalgProfileStat                       OBJECT IDENTIFIER ::= { ltmIpsecalg 2 }

--ltmHttp2
ltmHttp2Profile                  OBJECT IDENTIFIER ::= { ltmHttp2 1 }
ltmHttp2ProfileActivationModes   OBJECT IDENTIFIER ::= { ltmHttp2 2 }
ltmHttp2ProfileStat              OBJECT IDENTIFIER ::= { ltmHttp2 3 }

--ltmWebsocket
ltmWebsocketProfile                  OBJECT IDENTIFIER ::= { ltmWebsocket 1 }
ltmWebsocketProfileStat              OBJECT IDENTIFIER ::= { ltmWebsocket 2 }

--ltmTcpanalytics
ltmTcpanalyticsProfile           OBJECT IDENTIFIER ::= { ltmTcpanalytics 1 }

--ltmSplitsessionclient
ltmSplitsessionclientProfile         OBJECT IDENTIFIER ::= { ltmSplitsessionclient 1 }
ltmSplitsessionclientProfileStat     OBJECT IDENTIFIER ::= { ltmSplitsessionclient 2 }

--ltmSplitsessionserver
ltmSplitsessionserverProfile         OBJECT IDENTIFIER ::= { ltmSplitsessionserver 1 }
ltmSplitsessionserverProfileStat     OBJECT IDENTIFIER ::= { ltmSplitsessionserver 2 }

--ltmHttpProxyConnect
ltmHttpProxyConnectProfile           OBJECT IDENTIFIER ::= { ltmHttpProxyConnect 1 }
ltmHttpProxyConnectProfileStat       OBJECT IDENTIFIER ::= { ltmHttpProxyConnect 2 }

--ltmDiametersession
ltmDiametersessionProfile           OBJECT IDENTIFIER ::= { ltmDiametersession 1 }
ltmDiametersessionProfileStat       OBJECT IDENTIFIER ::= { ltmDiametersession 2 }

--ltmDiameterrouter
ltmDiameterrouterProfile           OBJECT IDENTIFIER ::= { ltmDiameterrouter 1 }
ltmDiameterrouterProfileStat       OBJECT IDENTIFIER ::= { ltmDiameterrouter 2 }

--ltmMrPmbrDiameter
ltmMrPmbrDiameterSessionStat       OBJECT IDENTIFIER ::= { ltmMrPmbrDiameter 1 }
ltmMrPmbrDiameterRouterStat        OBJECT IDENTIFIER ::= { ltmMrPmbrDiameter 2 }

--ltmSipsession
ltmSipsessionProfileStat       OBJECT IDENTIFIER ::= { ltmSipsession 1 }

--ltmSiprouter
ltmSiprouterProfileStat       OBJECT IDENTIFIER ::= { ltmSiprouter 1 }

--ltmMrPmbrSip
ltmMrPmbrSipSessionStat       OBJECT IDENTIFIER ::= { ltmMrPmbrSip 1 }
ltmMrPmbrSipRouterStat        OBJECT IDENTIFIER ::= { ltmMrPmbrSip 2 }



--==================================================================
-- Global
--==================================================================
ltmAttrLbmodeFastestMaxIdleTime OBJECT-TYPE
	SYNTAX Gauge
	MAX-ACCESS read-only
	STATUS	 deprecated
	DESCRIPTION
		"Deprecated!
		variable LBMode.FastertMaxIdleTime is purged"
	::= { ltmGlobalAttr 1 }

ltmAttrMirrorState OBJECT-TYPE
	SYNTAX INTEGER {
		disabled(0),
		enabled(1)
	}
	MAX-ACCESS read-only
	STATUS current
	DESCRIPTION
		"The state of mirroring in redundant systems."
	::= { ltmGlobalAttr 2 }

ltmAttrPersistDestAddrLimitMode OBJECT-TYPE
	SYNTAX INTEGER {
		timeout(0),
		maxcount(1)
	}
	MAX-ACCESS read-only
	STATUS current
	DESCRIPTION
		"The method of limiting destination address entries."
	::= { ltmGlobalAttr 3 }

ltmAttrPersistDestAddrMaxCount OBJECT-TYPE
	SYNTAX Gauge
	MAX-ACCESS read-only
	STATUS current
	DESCRIPTION
		"The maximum number of entries allowed for the destination address entries."
	::= { ltmGlobalAttr 4 }

ltmAttrSnatAnyIpProtocol OBJECT-TYPE
	SYNTAX INTEGER {
		disabled(0),
		enabled(1)
	}
	MAX-ACCESS read-only
	STATUS current
	DESCRIPTION
		"The status of the feature that allows any IP traffic
		 through SNATs."
	::= { ltmGlobalAttr 5 }

ltmAttrMirrorPeerIpAddr OBJECT-TYPE
	SYNTAX LongDisplayString
	MAX-ACCESS read-only
	STATUS current
	DESCRIPTION
		"The IP address of the mirroring peer in redundant systems"
	::= { ltmGlobalAttr 6 }

--==================================================================
-- Rate_filter_class
--==================================================================
ltmRateFilterNumber OBJECT-TYPE
	SYNTAX INTEGER
	MAX-ACCESS read-only
	STATUS current
	DESCRIPTION
		"The number of ltmRateFilter entries in the table."
	::= { ltmRateFilter 1 }

ltmRateFilterTable OBJECT-TYPE
	SYNTAX SEQUENCE OF LtmRateFilterEntry
	MAX-ACCESS not-accessible
	STATUS current
	DESCRIPTION
		"A table containing information of rate filters for shaping."
	::= { ltmRateFilter 2 }

ltmRateFilterEntry OBJECT-TYPE
	SYNTAX  LtmRateFilterEntry
	MAX-ACCESS not-accessible
	STATUS current
	DESCRIPTION
		"Columns in the ltmRateFilter Table"
	INDEX {
		ltmRateFilterCname
	}
	::= { ltmRateFilterTable 1 }

LtmRateFilterEntry ::=
	SEQUENCE {
        	ltmRateFilterCname                                        LongDisplayString,
        	ltmRateFilterRate                                         Gauge,
        	ltmRateFilterCeil                                         Gauge,
        	ltmRateFilterBurst                                        Gauge,
        	ltmRateFilterPname                                        LongDisplayString,
        	ltmRateFilterQtype                                        INTEGER,
        	ltmRateFilterDirection                                    INTEGER
	}

ltmRateFilterCname OBJECT-TYPE
	SYNTAX LongDisplayString
	MAX-ACCESS read-only
	STATUS current
	DESCRIPTION
		"The rate class name specified by the user according to the
		 same syntax allowed for rules or pool names"
	::= { ltmRateFilterEntry 1 }

ltmRateFilterRate OBJECT-TYPE
	SYNTAX Gauge
	MAX-ACCESS read-only
	STATUS current
	DESCRIPTION
		"The base rate. It is a number which may be postfixed with a
		 metric of either bps, Kbps or Mbps, to indicate bits per
		 second, Kilobits per second, or Megabits per second,
		 respectively.
		 Note: these numbers are powers of 10, not powers of 2.
		 If no postfix is specified, the number is interpreted as bps.
		 The rate specifies the maximum throughput to allot to traffic
		 handled by the Rate Class. Packets in excess of the posted
		 rate will be dropped."
	::= { ltmRateFilterEntry 2 }

ltmRateFilterCeil OBJECT-TYPE
	SYNTAX Gauge
	MAX-ACCESS read-only
	STATUS current
	DESCRIPTION
		"The ceiling rate. It is defined like the base rate, but specifies
		 how far beyond the base rate the traffic is allowed to flow
		 when bursting (details on bursting below). The ceiling rate is
		 an absolute limit - it is impossible for traffic to flow at a
		 higher rate than the ceiling rate, even when bursting. If the
		 ceiling rate is omitted or is equal to the base rate, the
		 traffic may not exceed the base rate. It is illegal for the
		 ceiling rate to be less than the base rate."
	::= { ltmRateFilterEntry 3 }

ltmRateFilterBurst OBJECT-TYPE
	SYNTAX Gauge
	MAX-ACCESS read-only
	STATUS current
	DESCRIPTION
		"The burst size. It specifies the maximum number of bytes the
		 traffic is allowed to burst when exceeding the base rate. The
		 burst size is measured in bytes. If omitted, a default burst
		size is 0."
	::= { ltmRateFilterEntry 4 }

ltmRateFilterPname OBJECT-TYPE
	SYNTAX LongDisplayString
	MAX-ACCESS read-only
	STATUS current
	DESCRIPTION
		"The parent rate class name. It indicates that the rate class
		 is a child of the named parent. Any child rate class has the
		 ability to borrow bandwidth from its parent. (Borrowing is a
		 feature which allows a child to burst even beyond the burst
		 size by borrowing from the burst size of a parent.) If omitted,
		 the rate class is not a child, but may be a parent if another
		 rate class refers to it as such."
	::= { ltmRateFilterEntry 5 }

ltmRateFilterQtype OBJECT-TYPE
	SYNTAX INTEGER {
		none(0),
		sfq(1),
		pfifo(2)
	}
	MAX-ACCESS read-only
	STATUS current
	DESCRIPTION
		"The queue discipline type.
		 none  - invalid state;
		 sfq   - stochastic fair queue;
		 pfifo - priority FIFO."
	::= { ltmRateFilterEntry 6 }

ltmRateFilterDirection OBJECT-TYPE
	SYNTAX INTEGER {
		any(0),
		client(1),
		server(2)
	}
	MAX-ACCESS read-only
	STATUS current
	DESCRIPTION
		"The state of the direction which the filter shapes traffic to.
		any    - shape to the client and server;
		client - only shape traffic to the client;
		server - only shape traffic to the server."
	::= { ltmRateFilterEntry 7 }

--==================================================================
-- Rate_filter_class_stat
--==================================================================
ltmRateFilterStatResetStats OBJECT-TYPE
	SYNTAX INTEGER
	MAX-ACCESS read-write
	STATUS current
	DESCRIPTION
		"The action to reset resettable statistics data in ltmRateFilterStat.
		 Setting this value to 1 will reset statistics data.
		 Note, some statistics data may not be reset including data that are incremental counters."
	::= { ltmRateFilterStat 1 }

ltmRateFilterStatNumber OBJECT-TYPE
	SYNTAX INTEGER
	MAX-ACCESS read-only
	STATUS current
	DESCRIPTION
		"The number of ltmRateFilterStat entries in the table."
	::= { ltmRateFilterStat 2 }

ltmRateFilterStatTable OBJECT-TYPE
	SYNTAX SEQUENCE OF LtmRateFilterStatEntry
	MAX-ACCESS not-accessible
	STATUS current
	DESCRIPTION
		"A table containing statistic information of rate filters for shaping."
	::= { ltmRateFilterStat 3 }

ltmRateFilterStatEntry OBJECT-TYPE
	SYNTAX  LtmRateFilterStatEntry
	MAX-ACCESS not-accessible
	STATUS current
	DESCRIPTION
		"Columns in the ltmRateFilterStat Table"
	INDEX {
		ltmRateFilterStatCname
	}
	::= { ltmRateFilterStatTable 1 }

LtmRateFilterStatEntry ::=
	SEQUENCE {
        	ltmRateFilterStatCname                                    LongDisplayString,
        	ltmRateFilterStatRateBytes                                Counter64,
        	ltmRateFilterStatBurstBytes                               Counter64,
        	ltmRateFilterStatDroppedBytes                             Counter64,
        	ltmRateFilterStatBytesQueued                              Counter64,
        	ltmRateFilterStatBytesPerSec                              Counter64,
        	ltmRateFilterStatDropTailPkts                             Counter64,
        	ltmRateFilterStatDropTailBytes                            Counter64,
        	ltmRateFilterStatDropRandPkts                             Counter64,
        	ltmRateFilterStatDropRandBytes                            Counter64,
        	ltmRateFilterStatDropTotPkts                              Counter64,
        	ltmRateFilterStatDropTotBytes                             Counter64
	}

ltmRateFilterStatCname OBJECT-TYPE
	SYNTAX LongDisplayString
	MAX-ACCESS read-only
	STATUS current
	DESCRIPTION
		"The rate class name specified by the user according to the
		 same syntax allowed for rules or pool names"
	::= { ltmRateFilterStatEntry 1 }

ltmRateFilterStatRateBytes OBJECT-TYPE
	SYNTAX Counter64
	MAX-ACCESS read-only
	STATUS current
	DESCRIPTION
		"The number of bytes at or below base rate - increments by 1 for
		 every byte of every packet handled at or below the base rate."
	::= { ltmRateFilterStatEntry 2 }

ltmRateFilterStatBurstBytes OBJECT-TYPE
	SYNTAX Counter64
	MAX-ACCESS read-only
	STATUS current
	DESCRIPTION
		"The number of bytes bursted (above base rate) - increments by
		 1 for every byte of every packet handled above the base rate
		 (i.e. bursted traffic)"
	::= { ltmRateFilterStatEntry 3 }

ltmRateFilterStatDroppedBytes OBJECT-TYPE
	SYNTAX Counter64
	MAX-ACCESS read-only
	STATUS	 deprecated
	DESCRIPTION
		"Deprecated!
		 Replaced by ltmRateFilterStatDropTotBytes:
		 the number of bytes dropped - increments by 1 for every byte
		 of every packet dropped by the rate class."
	::= { ltmRateFilterStatEntry 4 }

ltmRateFilterStatBytesQueued OBJECT-TYPE
	SYNTAX Counter64
	MAX-ACCESS read-only
	STATUS current
	DESCRIPTION
		"The number of bytes queued."
	::= { ltmRateFilterStatEntry 5 }

ltmRateFilterStatBytesPerSec OBJECT-TYPE
	SYNTAX Counter64
	MAX-ACCESS read-only
	STATUS current
	DESCRIPTION
		"The average bytes/sec over last 4 sec."
	::= { ltmRateFilterStatEntry 6 }

ltmRateFilterStatDropTailPkts OBJECT-TYPE
	SYNTAX Counter64
	MAX-ACCESS read-only
	STATUS current
	DESCRIPTION
		"The number of packets dropped - increments by 1 for
	         every packet dropped by the rate class as queue overflow."
	::= { ltmRateFilterStatEntry 7 }

ltmRateFilterStatDropTailBytes OBJECT-TYPE
	SYNTAX Counter64
	MAX-ACCESS read-only
	STATUS current
	DESCRIPTION
		"The number of bytes dropped - increments by 1 for every byte
	         of every packet dropped by the rate class as queue overflow."
	::= { ltmRateFilterStatEntry 8 }

ltmRateFilterStatDropRandPkts OBJECT-TYPE
	SYNTAX Counter64
	MAX-ACCESS read-only
	STATUS current
	DESCRIPTION
		"The number of packets dropped - increments by 1 for
	         every packet dropped by the rate class as RED or FRED policy."
	::= { ltmRateFilterStatEntry 9 }

ltmRateFilterStatDropRandBytes OBJECT-TYPE
	SYNTAX Counter64
	MAX-ACCESS read-only
	STATUS current
	DESCRIPTION
		"The  number of bytes dropped - increments by 1 for every byte
	         of every packet dropped by the rate class as RED or FRED policy."
	::= { ltmRateFilterStatEntry 10 }

ltmRateFilterStatDropTotPkts OBJECT-TYPE
	SYNTAX Counter64
	MAX-ACCESS read-only
	STATUS current
	DESCRIPTION
		"The total number of packets dropped - increments by 1 for
	         every packet dropped by the rate class."
	::= { ltmRateFilterStatEntry 11 }

ltmRateFilterStatDropTotBytes OBJECT-TYPE
	SYNTAX Counter64
	MAX-ACCESS read-only
	STATUS current
	DESCRIPTION
		"The total number of bytes dropped - increments by 1 for every byte
	         of every packet dropped by the rate class."
	::= { ltmRateFilterStatEntry 12 }

--==================================================================
-- Mirror_port
--==================================================================
ltmMirrorPortNumber OBJECT-TYPE
	SYNTAX INTEGER
	MAX-ACCESS read-only
	STATUS current
	DESCRIPTION
		"The number of ltmMirrorPort entries in the table."
	::= { ltmMirrorPort 1 }

ltmMirrorPortTable OBJECT-TYPE
	SYNTAX SEQUENCE OF LtmMirrorPortEntry
	MAX-ACCESS not-accessible
	STATUS current
	DESCRIPTION
		"A table containing information of mirrored ports."
	::= { ltmMirrorPort 2 }

ltmMirrorPortEntry OBJECT-TYPE
	SYNTAX  LtmMirrorPortEntry
	MAX-ACCESS not-accessible
	STATUS current
	DESCRIPTION
		"Columns in the ltmMirrorPort Table"
	INDEX {
		ltmMirrorPortName
	}
	::= { ltmMirrorPortTable 1 }

LtmMirrorPortEntry ::=
	SEQUENCE {
        	ltmMirrorPortName                                         LongDisplayString
	}

ltmMirrorPortName OBJECT-TYPE
	SYNTAX LongDisplayString
	MAX-ACCESS read-only
	STATUS current
	DESCRIPTION
		"The name of a port to which is mirrored."
	::= { ltmMirrorPortEntry 1 }

--==================================================================
-- Mirror_port_mbr
--==================================================================
ltmMirrorPortMemberNumber OBJECT-TYPE
	SYNTAX INTEGER
	MAX-ACCESS read-only
	STATUS current
	DESCRIPTION
		"The number of ltmMirrorPortMember entries in the table."
	::= { ltmMirrorPortMember 1 }

ltmMirrorPortMemberTable OBJECT-TYPE
	SYNTAX SEQUENCE OF LtmMirrorPortMemberEntry
	MAX-ACCESS not-accessible
	STATUS current
	DESCRIPTION
		"A table containing information of mirrored port members."
	::= { ltmMirrorPortMember 2 }

ltmMirrorPortMemberEntry OBJECT-TYPE
	SYNTAX  LtmMirrorPortMemberEntry
	MAX-ACCESS not-accessible
	STATUS current
	DESCRIPTION
		"Columns in the ltmMirrorPortMember Table"
	INDEX {
		ltmMirrorPortMemberToName,
		ltmMirrorPortMemberName
	}
	::= { ltmMirrorPortMemberTable 1 }

LtmMirrorPortMemberEntry ::=
	SEQUENCE {
        	ltmMirrorPortMemberToName                                 LongDisplayString,
        	ltmMirrorPortMemberName                                   LongDisplayString,
        	ltmMirrorPortMemberConduitName                            LongDisplayString
	}

ltmMirrorPortMemberToName OBJECT-TYPE
	SYNTAX LongDisplayString
	MAX-ACCESS read-only
	STATUS current
	DESCRIPTION
		"The name of a port which it is mirrored to."
	::= { ltmMirrorPortMemberEntry 1 }

ltmMirrorPortMemberName OBJECT-TYPE
	SYNTAX LongDisplayString
	MAX-ACCESS read-only
	STATUS current
	DESCRIPTION
		"The name of a mirrored port."
	::= { ltmMirrorPortMemberEntry 2 }

ltmMirrorPortMemberConduitName OBJECT-TYPE
	SYNTAX LongDisplayString
	MAX-ACCESS read-only
	STATUS current
	DESCRIPTION
		"This attribute is used to represent a local edge port
		when a conduit between switch devices is necessary."
	::= { ltmMirrorPortMemberEntry 3 }

--==================================================================
-- Nat
--==================================================================
ltmNatNumber OBJECT-TYPE
	SYNTAX INTEGER
	MAX-ACCESS read-only
	STATUS current
	DESCRIPTION
		"The number of ltmNat entries in the table."
	::= { ltmNat 1 }

ltmNatTable OBJECT-TYPE
	SYNTAX SEQUENCE OF LtmNatEntry
	MAX-ACCESS not-accessible
	STATUS current
	DESCRIPTION
		"A table containing information of NAT."
	::= { ltmNat 2 }

ltmNatEntry OBJECT-TYPE
	SYNTAX  LtmNatEntry
	MAX-ACCESS not-accessible
	STATUS current
	DESCRIPTION
		"Columns in the ltmNat Table"
	INDEX {
		ltmNatName
	}
	::= { ltmNatTable 1 }

LtmNatEntry ::=
	SEQUENCE {
        	ltmNatTransAddrType                                       InetAddressType,
        	ltmNatTransAddr                                           InetAddress,
        	ltmNatOrigAddrType                                        InetAddressType,
        	ltmNatOrigAddr                                            InetAddress,
        	ltmNatEnabled                                             INTEGER,
        	ltmNatArpEnabled                                          INTEGER,
        	ltmNatUnitId                                              Gauge,
        	ltmNatListedEnabledVlans                                  INTEGER,
        	ltmNatName                                                LongDisplayString
	}

ltmNatTransAddrType OBJECT-TYPE
	SYNTAX InetAddressType
	MAX-ACCESS read-only
	STATUS current
	DESCRIPTION
		"The IP address type of ltmNatTransAddr"
	::= { ltmNatEntry 1 }

ltmNatTransAddr OBJECT-TYPE
	SYNTAX InetAddress
	MAX-ACCESS read-only
	STATUS current
	DESCRIPTION
		"The NAT translation address. It is
		interpreted within the context of a ltmNatTransAddrType value."
	::= { ltmNatEntry 2 }

ltmNatOrigAddrType OBJECT-TYPE
	SYNTAX InetAddressType
	MAX-ACCESS read-only
	STATUS current
	DESCRIPTION
		"The IP address type of ltmNatOrigAddr."
	::= { ltmNatEntry 3 }

ltmNatOrigAddr OBJECT-TYPE
	SYNTAX InetAddress
	MAX-ACCESS read-only
	STATUS current
	DESCRIPTION
		"The NAT original address associated with the specified NAT translation address.
		It is interpreted within the context of a ltmNatOrigAddrType value."
	::= { ltmNatEntry 4 }

ltmNatEnabled OBJECT-TYPE
	SYNTAX INTEGER {
		false(0),
		true(1)
	}
	MAX-ACCESS read-only
	STATUS current
	DESCRIPTION
		"The state indicating whether the specified NAT address is enabled or not."
	::= { ltmNatEntry 5 }

ltmNatArpEnabled OBJECT-TYPE
	SYNTAX INTEGER {
		false(0),
		true(1)
	}
	MAX-ACCESS read-only
	STATUS current
	DESCRIPTION
		"The ARP state for the specified NAT, whether it is enabled or not."
	::= { ltmNatEntry 6 }

ltmNatUnitId OBJECT-TYPE
	SYNTAX Gauge
	MAX-ACCESS read-only
	STATUS current
	DESCRIPTION
		"The unit number associated with the specified NAT translation address."
	::= { ltmNatEntry 7 }

ltmNatListedEnabledVlans OBJECT-TYPE
	SYNTAX INTEGER {
		false(0),
		true(1)
	}
	MAX-ACCESS read-only
	STATUS current
	DESCRIPTION
		"The state indicating whether associated VLANs are NAT enabled or not.
		The associated VLANs are listed in ltmNatVlanTable."
	::= { ltmNatEntry 8 }

ltmNatName OBJECT-TYPE
	SYNTAX LongDisplayString
	MAX-ACCESS read-only
	STATUS current
	DESCRIPTION
		"Name of the nat"
	::= { ltmNatEntry 9 }

--==================================================================
-- Nat_stat
--==================================================================
ltmNatStatResetStats OBJECT-TYPE
	SYNTAX INTEGER
	MAX-ACCESS read-write
	STATUS current
	DESCRIPTION
		"The action to reset resettable statistics data in ltmNatStat.
		 Setting this value to 1 will reset statistics data.
		 Note, some statistics data may not be reset including data that are incremental counters."
	::= { ltmNatStat 1 }

ltmNatStatNumber OBJECT-TYPE
	SYNTAX INTEGER
	MAX-ACCESS read-only
	STATUS current
	DESCRIPTION
		"The number of ltmNatStat entries in the table."
	::= { ltmNatStat 2 }

ltmNatStatTable OBJECT-TYPE
	SYNTAX SEQUENCE OF LtmNatStatEntry
	MAX-ACCESS not-accessible
	STATUS current
	DESCRIPTION
		"A table containing statistic information of NAT."
	::= { ltmNatStat 3 }

ltmNatStatEntry OBJECT-TYPE
	SYNTAX  LtmNatStatEntry
	MAX-ACCESS not-accessible
	STATUS current
	DESCRIPTION
		"Columns in the ltmNatStat Table"
	INDEX {
		ltmNatStatName
	}
	::= { ltmNatStatTable 1 }

LtmNatStatEntry ::=
	SEQUENCE {
        	ltmNatStatTransAddrType                                   InetAddressType,
        	ltmNatStatTransAddr                                       InetAddress,
        	ltmNatStatServerPktsIn                                    Counter64,
        	ltmNatStatServerBytesIn                                   Counter64,
        	ltmNatStatServerPktsOut                                   Counter64,
        	ltmNatStatServerBytesOut                                  Counter64,
        	ltmNatStatServerMaxConns                                  Counter64,
        	ltmNatStatServerTotConns                                  Counter64,
        	ltmNatStatServerCurConns                                  Gauge,
        	ltmNatStatName                                            LongDisplayString
	}

ltmNatStatTransAddrType OBJECT-TYPE
	SYNTAX InetAddressType
	MAX-ACCESS read-only
	STATUS	 deprecated
	DESCRIPTION
		"Deprecated!
		 The IP address type of ltmNatStatTransAddr"
	::= { ltmNatStatEntry 1 }

ltmNatStatTransAddr OBJECT-TYPE
	SYNTAX InetAddress
	MAX-ACCESS read-only
	STATUS	 deprecated
	DESCRIPTION
		"Deprecated!
		The NAT translation address. It is
		interpreted within the context of a ltmNatStatTransAddrType value."
	::= { ltmNatStatEntry 2 }

ltmNatStatServerPktsIn OBJECT-TYPE
	SYNTAX Counter64
	MAX-ACCESS read-only
	STATUS current
	DESCRIPTION
		"The number of packets received from server-side."
	::= { ltmNatStatEntry 3 }

ltmNatStatServerBytesIn OBJECT-TYPE
	SYNTAX Counter64
	MAX-ACCESS read-only
	STATUS current
	DESCRIPTION
		"The number of bytes received from server-side."
	::= { ltmNatStatEntry 4 }

ltmNatStatServerPktsOut OBJECT-TYPE
	SYNTAX Counter64
	MAX-ACCESS read-only
	STATUS current
	DESCRIPTION
		"The number of packets sent to server-side."
	::= { ltmNatStatEntry 5 }

ltmNatStatServerBytesOut OBJECT-TYPE
	SYNTAX Counter64
	MAX-ACCESS read-only
	STATUS current
	DESCRIPTION
		"The number of bytes sent to server-side."
	::= { ltmNatStatEntry 6 }

ltmNatStatServerMaxConns OBJECT-TYPE
	SYNTAX Counter64
	MAX-ACCESS read-only
	STATUS current
	DESCRIPTION
		"The maximum connections from server-side."
	::= { ltmNatStatEntry 7 }

ltmNatStatServerTotConns OBJECT-TYPE
	SYNTAX Counter64
	MAX-ACCESS read-only
	STATUS current
	DESCRIPTION
		"The total connections from server-side."
	::= { ltmNatStatEntry 8 }

ltmNatStatServerCurConns OBJECT-TYPE
	SYNTAX Gauge
	MAX-ACCESS read-only
	STATUS current
	DESCRIPTION
		"The current connections from server-side."
	::= { ltmNatStatEntry 9 }

ltmNatStatName OBJECT-TYPE
	SYNTAX LongDisplayString
	MAX-ACCESS read-only
	STATUS current
	DESCRIPTION
		"Name of the nat"
	::= { ltmNatStatEntry 10 }

--==================================================================
-- Nat_vlan
--==================================================================
ltmNatVlanNumber OBJECT-TYPE
	SYNTAX INTEGER
	MAX-ACCESS read-only
	STATUS current
	DESCRIPTION
		"The number of ltmNatVlan entries in the table."
	::= { ltmNatVlan 1 }

ltmNatVlanTable OBJECT-TYPE
	SYNTAX SEQUENCE OF LtmNatVlanEntry
	MAX-ACCESS not-accessible
	STATUS current
	DESCRIPTION
		"A table containing VLAN information associated with NAT."
	::= { ltmNatVlan 2 }

ltmNatVlanEntry OBJECT-TYPE
	SYNTAX  LtmNatVlanEntry
	MAX-ACCESS not-accessible
	STATUS current
	DESCRIPTION
		"Columns in the ltmNatVlan Table"
	INDEX {
		ltmNatVlanNatName,
		ltmNatVlanVlanName
	}
	::= { ltmNatVlanTable 1 }

LtmNatVlanEntry ::=
	SEQUENCE {
        	ltmNatVlanTransAddrType                                   InetAddressType,
        	ltmNatVlanTransAddr                                       InetAddress,
        	ltmNatVlanVlanName                                        LongDisplayString,
        	ltmNatVlanNatName                                         LongDisplayString
	}

ltmNatVlanTransAddrType OBJECT-TYPE
	SYNTAX InetAddressType
	MAX-ACCESS read-only
	STATUS	 deprecated
	DESCRIPTION
		"Deprecated! Use nat_name to associate vlan to NAT.
		 The IP address type of ltmNatVlanTransAddr"
	::= { ltmNatVlanEntry 1 }

ltmNatVlanTransAddr OBJECT-TYPE
	SYNTAX InetAddress
	MAX-ACCESS read-only
	STATUS	 deprecated
	DESCRIPTION
		"Deprecated! Use nat_name to associate vlan to NAT.
		The NAT translation address. It is interpreted within
		the context of a ltmNatVlanTransAddrType value."
	::= { ltmNatVlanEntry 2 }

ltmNatVlanVlanName OBJECT-TYPE
	SYNTAX LongDisplayString
	MAX-ACCESS read-only
	STATUS current
	DESCRIPTION
		"The name of a VLAN associated with the specified NAT.
		Only when ltmNatListedEnabledVlans is set to enable,
		NAT is enabled on the VLAN. "
	::= { ltmNatVlanEntry 3 }

ltmNatVlanNatName OBJECT-TYPE
	SYNTAX LongDisplayString
	MAX-ACCESS read-only
	STATUS current
	DESCRIPTION
		"Name of the nat"
	::= { ltmNatVlanEntry 4 }

--==================================================================
-- Node_address
--==================================================================
ltmNodeAddrNumber OBJECT-TYPE
	SYNTAX INTEGER
	MAX-ACCESS read-only
	STATUS current
	DESCRIPTION
		"The number of ltmNodeAddr entries in the table."
	::= { ltmNodeAddr 1 }

ltmNodeAddrTable OBJECT-TYPE
	SYNTAX SEQUENCE OF LtmNodeAddrEntry
	MAX-ACCESS not-accessible
	STATUS current
	DESCRIPTION
		"A table containing information of node addresses."
	::= { ltmNodeAddr 2 }

ltmNodeAddrEntry OBJECT-TYPE
	SYNTAX  LtmNodeAddrEntry
	MAX-ACCESS not-accessible
	STATUS current
	DESCRIPTION
		"Columns in the ltmNodeAddr Table"
	INDEX {
		ltmNodeAddrName
	}
	::= { ltmNodeAddrTable 1 }

LtmNodeAddrEntry ::=
	SEQUENCE {
        	ltmNodeAddrAddrType                                       InetAddressType,
        	ltmNodeAddrAddr                                           InetAddress,
        	ltmNodeAddrConnLimit                                      Gauge,
        	ltmNodeAddrRatio                                          Gauge,
        	ltmNodeAddrDynamicRatio                                   INTEGER,
        	ltmNodeAddrMonitorState                                   INTEGER,
        	ltmNodeAddrMonitorStatus                                  INTEGER,
        	ltmNodeAddrMonitorRule                                    LongDisplayString,
        	ltmNodeAddrNewSessionEnable                               INTEGER,
        	ltmNodeAddrSessionStatus                                  INTEGER,
        	ltmNodeAddrPoolMemberRefCount                             Gauge,
        	ltmNodeAddrScreenName                                     LongDisplayString,
        	ltmNodeAddrAvailabilityState                              INTEGER,
        	ltmNodeAddrEnabledState                                   INTEGER,
        	ltmNodeAddrDisabledParentType                             Gauge,
        	ltmNodeAddrStatusReason                                   LongDisplayString,
        	ltmNodeAddrName                                           LongDisplayString
	}

ltmNodeAddrAddrType OBJECT-TYPE
	SYNTAX InetAddressType
	MAX-ACCESS read-only
	STATUS current
	DESCRIPTION
		"The IP address type of ltmNodeAddrAddr."
	::= { ltmNodeAddrEntry 1 }

ltmNodeAddrAddr OBJECT-TYPE
	SYNTAX InetAddress
	MAX-ACCESS read-only
	STATUS current
	DESCRIPTION
		"The IP address of a node. It is interpreted within
		 the context of a ltmNodeAddrAddrType value."
	::= { ltmNodeAddrEntry 2 }

ltmNodeAddrConnLimit OBJECT-TYPE
	SYNTAX Gauge
	MAX-ACCESS read-only
	STATUS current
	DESCRIPTION
		"The maximum number of connections the specified node address is
		 allowed to have open at one time."
	::= { ltmNodeAddrEntry 3 }

ltmNodeAddrRatio OBJECT-TYPE
	SYNTAX Gauge
	MAX-ACCESS read-only
	STATUS current
	DESCRIPTION
		"The ratio of the specified node address, used in load balance algorithm."
	::= { ltmNodeAddrEntry 4 }

ltmNodeAddrDynamicRatio OBJECT-TYPE
	SYNTAX INTEGER
	MAX-ACCESS read-only
	STATUS current
	DESCRIPTION
		"The dynamic ratio of the specified node address, used in load balance algorithm."
	::= { ltmNodeAddrEntry 5 }

ltmNodeAddrMonitorState OBJECT-TYPE
	SYNTAX INTEGER {
		unchecked(0),
		checking(1),
		inband(2),
		forcedUp(3),
		up(4),
		down(19),
		forcedDown(20),
		iruleDown(22),
		inbandDown(23),
		downManualResume(24),
		disabled(25),
		fqdnChecking(26),
		fqdnDown(27),
		fqdnUp(28),
		fqdnUpNoAddress(29)
	}
	MAX-ACCESS read-write
	STATUS current
	DESCRIPTION
		"The internal tmm monitor state for the specified node address."
	::= { ltmNodeAddrEntry 6 }

ltmNodeAddrMonitorStatus OBJECT-TYPE
	SYNTAX INTEGER {
		unchecked(0),
		checking(1),
		inband(2),
		forcedUp(3),
		up(4),
		addrDown(18),
		down(19),
		forcedDown(20),
		maint(21),
		iruleDown(22),
		inbandDown(23),
		downManualResume(24),
		fqdnChecking(26),
		fqdnDown(27),
		fqdnUp(28),
		fqdnUpNoAddress(29)
	}
	MAX-ACCESS read-only
	STATUS current
	DESCRIPTION
		"The hierarchical load balance state for the specified node address, including parent status.
		 unchecked - enabled node that is not monitored;
		 checking  - initial state until monitor reports;
		 inband    - the tmm has marked the node up;
		 forcedUp - forced up manually;
		 up        - enabled node when its monitors succeed;
		 addrDown   - node address monitor fails or forced down;
		 down        - enabled node when its monitors fail;
		 forcedDown  - node forced down manually;
		 maint       - in maintenance mode;
		 iruleDown   - an iRule has marked the node down;
		 inbandDown  - the tmm has marked the node down;
		 downManualResume - the node is down and must be manually enabled;
		 fqdnChecking - initial fqdn node state until monitor reports;
		 fqdnDown    - enabled fqdn node when its monitors fail;
		 fqdnUp      - enabled fqdn node when its monitors succeed;
		 fqdnUpNoAddress - no dns records returned for fqdn node;
		 "
	::= { ltmNodeAddrEntry 7 }

ltmNodeAddrMonitorRule OBJECT-TYPE
	SYNTAX LongDisplayString
	MAX-ACCESS read-only
	STATUS current
	DESCRIPTION
		"The monitor rule used for load balance the specified node address."
	::= { ltmNodeAddrEntry 8 }

ltmNodeAddrNewSessionEnable OBJECT-TYPE
	SYNTAX INTEGER {
		userDisabled(1),
		userEnabled(2),
		monitorEnabled(3),
		monitorDisabled(4)
	}
	MAX-ACCESS read-only
	STATUS	 deprecated
	DESCRIPTION
		"Deprecated!
		 The state indicating whether a new session can be enabled or not for the specified node address."
	::= { ltmNodeAddrEntry 9 }

ltmNodeAddrSessionStatus OBJECT-TYPE
	SYNTAX INTEGER {
		enabled(1),
		addrdisabled(2),
		servdisabled(3),
		disabled(4),
		forceddisabled(5)
	}
	MAX-ACCESS read-only
	STATUS current
	DESCRIPTION
		"The hierarchical status of the session, including parent status, for
		the specified node address.
		enabled       - new sessions enabled;
		addrdisabled - new sessions disabled on node address;
		servdisabled - new sessions disabled on node server;
		disabled      - new sessions disabled;
		forceddisabled - new sessions forced to be disabled."
	::= { ltmNodeAddrEntry 10 }

ltmNodeAddrPoolMemberRefCount OBJECT-TYPE
	SYNTAX Gauge
	MAX-ACCESS read-only
	STATUS	 deprecated
	DESCRIPTION
		"Deprecated!
	        Node Address tracking method changed. The node address member reference count is no longer used."
	::= { ltmNodeAddrEntry 11 }

ltmNodeAddrScreenName OBJECT-TYPE
	SYNTAX LongDisplayString
	MAX-ACCESS read-only
	STATUS	 deprecated
	DESCRIPTION
		"Deprecated! This field is removed.
		The screen names for the specified node address."
	::= { ltmNodeAddrEntry 12 }

ltmNodeAddrAvailabilityState OBJECT-TYPE
	SYNTAX INTEGER {
		none(0),
		green(1),
		yellow(2),
		red(3),
		blue(4)
	}
	MAX-ACCESS read-only
	STATUS	 deprecated
	DESCRIPTION
		"Deprecated!
		Replaced by ltmNodeAddrStatusAvailState under ltmNodeAddrStatus.
		The state of the specified node address availability indicated in color."
	::= { ltmNodeAddrEntry 13 }

ltmNodeAddrEnabledState OBJECT-TYPE
	SYNTAX INTEGER {
		none(0),
		enabled(1),
		disabled(2),
		disabledbyparent(3)
	}
	MAX-ACCESS read-only
	STATUS	 deprecated
	DESCRIPTION
		"Deprecated!
		Replaced by ltmNodeAddrStatusEnabledState under ltmNodeAddrStatus.
		The state of the specified node address activity status, as specified
		by the user."
	::= { ltmNodeAddrEntry 14 }

ltmNodeAddrDisabledParentType OBJECT-TYPE
	SYNTAX Gauge
	MAX-ACCESS read-only
	STATUS	 deprecated
	DESCRIPTION
		"Deprecated!
		Replaced by ltmNodeAddrStatusParentType under ltmNodeAddrStatus.
		The type of parent object which disabled the specified node address."
	::= { ltmNodeAddrEntry 15 }

ltmNodeAddrStatusReason OBJECT-TYPE
	SYNTAX LongDisplayString
	MAX-ACCESS read-only
	STATUS	 deprecated
	DESCRIPTION
		"Deprecated!
		Replaced by ltmNodeAddrStatusDetailReason under ltmNodeAddrStatus.
		The detail description of the node's status of parent object
		which disabled the specified node address."
	::= { ltmNodeAddrEntry 16 }

ltmNodeAddrName OBJECT-TYPE
	SYNTAX LongDisplayString
	MAX-ACCESS read-only
	STATUS current
	DESCRIPTION
		"node name."
	::= { ltmNodeAddrEntry 17 }

--==================================================================
-- Node_address_stat
--==================================================================
ltmNodeAddrStatResetStats OBJECT-TYPE
	SYNTAX INTEGER
	MAX-ACCESS read-write
	STATUS current
	DESCRIPTION
		"The action to reset resettable statistics data in ltmNodeAddrStat.
		 Setting this value to 1 will reset statistics data.
		 Note, some statistics data may not be reset including data that are incremental counters."
	::= { ltmNodeAddrStat 1 }

ltmNodeAddrStatNumber OBJECT-TYPE
	SYNTAX INTEGER
	MAX-ACCESS read-only
	STATUS current
	DESCRIPTION
		"The number of ltmNodeAddrStat entries in the table."
	::= { ltmNodeAddrStat 2 }

ltmNodeAddrStatTable OBJECT-TYPE
	SYNTAX SEQUENCE OF LtmNodeAddrStatEntry
	MAX-ACCESS not-accessible
	STATUS current
	DESCRIPTION
		"A table containing statistic information of node addresses."
	::= { ltmNodeAddrStat 3 }

ltmNodeAddrStatEntry OBJECT-TYPE
	SYNTAX  LtmNodeAddrStatEntry
	MAX-ACCESS not-accessible
	STATUS current
	DESCRIPTION
		"Columns in the ltmNodeAddrStat Table"
	INDEX {
		ltmNodeAddrStatNodeName
	}
	::= { ltmNodeAddrStatTable 1 }

LtmNodeAddrStatEntry ::=
	SEQUENCE {
        	ltmNodeAddrStatAddrType                                   InetAddressType,
        	ltmNodeAddrStatAddr                                       InetAddress,
        	ltmNodeAddrStatServerPktsIn                               Counter64,
        	ltmNodeAddrStatServerBytesIn                              Counter64,
        	ltmNodeAddrStatServerPktsOut                              Counter64,
        	ltmNodeAddrStatServerBytesOut                             Counter64,
        	ltmNodeAddrStatServerMaxConns                             Counter64,
        	ltmNodeAddrStatServerTotConns                             Counter64,
        	ltmNodeAddrStatServerCurConns                             Gauge,
        	ltmNodeAddrStatPvaPktsIn                                  Counter64,
        	ltmNodeAddrStatPvaBytesIn                                 Counter64,
        	ltmNodeAddrStatPvaPktsOut                                 Counter64,
        	ltmNodeAddrStatPvaBytesOut                                Counter64,
        	ltmNodeAddrStatPvaMaxConns                                Counter64,
        	ltmNodeAddrStatPvaTotConns                                Counter64,
        	ltmNodeAddrStatPvaCurConns                                Gauge,
        	ltmNodeAddrStatTotRequests                                Counter64,
        	ltmNodeAddrStatTotPvaAssistConn                           Counter64,
        	ltmNodeAddrStatCurrPvaAssistConn                          Gauge,
        	ltmNodeAddrStatNodeName                                   LongDisplayString,
        	ltmNodeAddrStatCurSessions                                Gauge,
        	ltmNodeAddrStatCurrentConnsPerSec                         Gauge,
        	ltmNodeAddrStatDurationRateExceeded                       Gauge
	}

ltmNodeAddrStatAddrType OBJECT-TYPE
	SYNTAX InetAddressType
	MAX-ACCESS read-only
	STATUS	 deprecated
	DESCRIPTION
		"Deprecated! use node_name instead,
	    The IP address type of ltmNodeAddrStatAddr"
	::= { ltmNodeAddrStatEntry 1 }

ltmNodeAddrStatAddr OBJECT-TYPE
	SYNTAX InetAddress
	MAX-ACCESS read-only
	STATUS	 deprecated
	DESCRIPTION
		"Deprecated! use node_name instead,
		 The IP address of a node. It is interpreted within
		 the context of an ltmNodeAddrStatAddrType value."
	::= { ltmNodeAddrStatEntry 2 }

ltmNodeAddrStatServerPktsIn OBJECT-TYPE
	SYNTAX Counter64
	MAX-ACCESS read-only
	STATUS current
	DESCRIPTION
		"The number of packets received by the specified node address from server-side."
	::= { ltmNodeAddrStatEntry 3 }

ltmNodeAddrStatServerBytesIn OBJECT-TYPE
	SYNTAX Counter64
	MAX-ACCESS read-only
	STATUS current
	DESCRIPTION
		"The number of bytes received by the specified node address from server-side."
	::= { ltmNodeAddrStatEntry 4 }

ltmNodeAddrStatServerPktsOut OBJECT-TYPE
	SYNTAX Counter64
	MAX-ACCESS read-only
	STATUS current
	DESCRIPTION
		"The number of packets sent to server-side from the specified node address."
	::= { ltmNodeAddrStatEntry 5 }

ltmNodeAddrStatServerBytesOut OBJECT-TYPE
	SYNTAX Counter64
	MAX-ACCESS read-only
	STATUS current
	DESCRIPTION
		"The number of bytes sent to server-side from the specified node address."
	::= { ltmNodeAddrStatEntry 6 }

ltmNodeAddrStatServerMaxConns OBJECT-TYPE
	SYNTAX Counter64
	MAX-ACCESS read-only
	STATUS current
	DESCRIPTION
		"The maximum connections from server-side to the specified node address."
	::= { ltmNodeAddrStatEntry 7 }

ltmNodeAddrStatServerTotConns OBJECT-TYPE
	SYNTAX Counter64
	MAX-ACCESS read-only
	STATUS current
	DESCRIPTION
		"The total connections from server-side to the specified node address."
	::= { ltmNodeAddrStatEntry 8 }

ltmNodeAddrStatServerCurConns OBJECT-TYPE
	SYNTAX Gauge
	MAX-ACCESS read-only
	STATUS current
	DESCRIPTION
		"The current connections from server-side to the specified node address."
	::= { ltmNodeAddrStatEntry 9 }

ltmNodeAddrStatPvaPktsIn OBJECT-TYPE
	SYNTAX Counter64
	MAX-ACCESS read-only
	STATUS current
	DESCRIPTION
		"The total number of hardware accelerated packets received by the specified node address."
	::= { ltmNodeAddrStatEntry 10 }

ltmNodeAddrStatPvaBytesIn OBJECT-TYPE
	SYNTAX Counter64
	MAX-ACCESS read-only
	STATUS current
	DESCRIPTION
		"The total number of hardware accelerated bytes received by the specified node address."
	::= { ltmNodeAddrStatEntry 11 }

ltmNodeAddrStatPvaPktsOut OBJECT-TYPE
	SYNTAX Counter64
	MAX-ACCESS read-only
	STATUS current
	DESCRIPTION
		"The total number of hardware accelerated packets sent out from the specified node address."
	::= { ltmNodeAddrStatEntry 12 }

ltmNodeAddrStatPvaBytesOut OBJECT-TYPE
	SYNTAX Counter64
	MAX-ACCESS read-only
	STATUS current
	DESCRIPTION
		"The number of hardware accelerated bytes sent out from the specified node address."
	::= { ltmNodeAddrStatEntry 13 }

ltmNodeAddrStatPvaMaxConns OBJECT-TYPE
	SYNTAX Counter64
	MAX-ACCESS read-only
	STATUS current
	DESCRIPTION
		"The maximum hardware accelerated connections to the specified node address."
	::= { ltmNodeAddrStatEntry 14 }

ltmNodeAddrStatPvaTotConns OBJECT-TYPE
	SYNTAX Counter64
	MAX-ACCESS read-only
	STATUS current
	DESCRIPTION
		"The total hardware accelerated connections to the specified node address."
	::= { ltmNodeAddrStatEntry 15 }

ltmNodeAddrStatPvaCurConns OBJECT-TYPE
	SYNTAX Gauge
	MAX-ACCESS read-only
	STATUS current
	DESCRIPTION
		"The current hardware accelerated connections to the specified node address."
	::= { ltmNodeAddrStatEntry 16 }

ltmNodeAddrStatTotRequests OBJECT-TYPE
	SYNTAX Counter64
	MAX-ACCESS read-only
	STATUS current
	DESCRIPTION
		"The total number of requests going through the specified node address."
	::= { ltmNodeAddrStatEntry 17 }

ltmNodeAddrStatTotPvaAssistConn OBJECT-TYPE
	SYNTAX Counter64
	MAX-ACCESS read-only
	STATUS current
	DESCRIPTION
		"The total number of connections to the specified node address,
		which are partially hardware accelerated."
	::= { ltmNodeAddrStatEntry 18 }

ltmNodeAddrStatCurrPvaAssistConn OBJECT-TYPE
	SYNTAX Gauge
	MAX-ACCESS read-only
	STATUS current
	DESCRIPTION
		"The current number of connections to the specified node address,
		 which are partially hardware accelerated."
	::= { ltmNodeAddrStatEntry 19 }

ltmNodeAddrStatNodeName OBJECT-TYPE
	SYNTAX LongDisplayString
	MAX-ACCESS read-only
	STATUS current
	DESCRIPTION
		"node name"
	::= { ltmNodeAddrStatEntry 20 }

ltmNodeAddrStatCurSessions OBJECT-TYPE
	SYNTAX Gauge
	MAX-ACCESS read-only
	STATUS current
	DESCRIPTION
		"The number of current sessions going through the specified node address."
	::= { ltmNodeAddrStatEntry 21 }

ltmNodeAddrStatCurrentConnsPerSec OBJECT-TYPE
	SYNTAX Gauge
	MAX-ACCESS read-only
	STATUS current
	DESCRIPTION
		"The last recorded value for the number of connections to the node address when connections hit a rate limit; this calculation is only maintained if rate limiting is configured for the node."
	::= { ltmNodeAddrStatEntry 22 }

ltmNodeAddrStatDurationRateExceeded OBJECT-TYPE
	SYNTAX Gauge
	MAX-ACCESS read-only
	STATUS current
	DESCRIPTION
		"Duration of time in seconds the specified node address has exceeded the
		configured connection rate limit."
	::= { ltmNodeAddrStatEntry 23 }

--==================================================================
-- Pool
--==================================================================
ltmPoolNumber OBJECT-TYPE
	SYNTAX INTEGER
	MAX-ACCESS read-only
	STATUS current
	DESCRIPTION
		"The number of ltmPool entries in the table."
	::= { ltmPool 1 }

ltmPoolTable OBJECT-TYPE
	SYNTAX SEQUENCE OF LtmPoolEntry
	MAX-ACCESS not-accessible
	STATUS current
	DESCRIPTION
		"A table containing information of pools."
	::= { ltmPool 2 }

ltmPoolEntry OBJECT-TYPE
	SYNTAX  LtmPoolEntry
	MAX-ACCESS not-accessible
	STATUS current
	DESCRIPTION
		"Columns in the ltmPool Table"
	INDEX {
		ltmPoolName
	}
	::= { ltmPoolTable 1 }

LtmPoolEntry ::=
	SEQUENCE {
        	ltmPoolName                                               LongDisplayString,
        	ltmPoolLbMode                                             INTEGER,
        	ltmPoolActionOnServiceDown                                INTEGER,
        	ltmPoolMinUpMembers                                       INTEGER,
        	ltmPoolMinUpMembersEnable                                 INTEGER,
        	ltmPoolMinUpMemberAction                                  INTEGER,
        	ltmPoolMinActiveMembers                                   INTEGER,
        	ltmPoolActiveMemberCnt                                    INTEGER,
        	ltmPoolDisallowSnat                                       INTEGER,
        	ltmPoolDisallowNat                                        INTEGER,
        	ltmPoolSimpleTimeout                                      Gauge,
        	ltmPoolIpTosToClient                                      INTEGER,
        	ltmPoolIpTosToServer                                      INTEGER,
        	ltmPoolLinkQosToClient                                    INTEGER,
        	ltmPoolLinkQosToServer                                    INTEGER,
        	ltmPoolDynamicRatioSum                                    Gauge,
        	ltmPoolMonitorRule                                        LongDisplayString,
        	ltmPoolAvailabilityState                                  INTEGER,
        	ltmPoolEnabledState                                       INTEGER,
        	ltmPoolDisabledParentType                                 Gauge,
        	ltmPoolStatusReason                                       LongDisplayString,
        	ltmPoolSlowRampTime                                       Gauge,
        	ltmPoolMemberCnt                                          Gauge,
        	ltmPoolQueueOnConnectionLimit                             INTEGER,
        	ltmPoolQueueDepthLimit                                    Gauge,
        	ltmPoolQueueTimeLimit                                     Gauge,
        	ltmPoolDescription                                        LongDisplayString
	}

ltmPoolName OBJECT-TYPE
	SYNTAX LongDisplayString
	MAX-ACCESS read-only
	STATUS current
	DESCRIPTION
		"The name of a pool."
	::= { ltmPoolEntry 1 }

ltmPoolLbMode OBJECT-TYPE
	SYNTAX INTEGER {
		roundRobin(0),
		ratioMember(1),
		leastConnMember(2),
		observedMember(3),
		predictiveMember(4),
		ratioNodeAddress(5),
		leastConnNodeAddress(6),
		fastestNodeAddress(7),
		observedNodeAddress(8),
		predictiveNodeAddress(9),
		dynamicRatio(10),
		fastestAppResponse(11),
		leastSessions(12),
		dynamicRatioMember(13),
		l3Addr(14),
		weightedLeastConnMember(15),
		weightedLeastConnNodeAddr(16),
		ratioSession(17)
	}
	MAX-ACCESS read-only
	STATUS current
	DESCRIPTION
		"The load balance method for this pool"
	::= { ltmPoolEntry 2 }

ltmPoolActionOnServiceDown OBJECT-TYPE
	SYNTAX INTEGER {
		none(0),
		reset(1),
		drop(2),
		reselect(3)
	}
	MAX-ACCESS read-only
	STATUS current
	DESCRIPTION
		"The action to be taken if the service for the specified pool is down."
	::= { ltmPoolEntry 3 }

ltmPoolMinUpMembers OBJECT-TYPE
	SYNTAX INTEGER
	MAX-ACCESS read-only
	STATUS current
	DESCRIPTION
		"The minimum number of UP members required for the specified pool
		before a high availability action to be taken.
		This is used when ltmPoolMinUpMembersEnable is true."
	::= { ltmPoolEntry 4 }

ltmPoolMinUpMembersEnable OBJECT-TYPE
	SYNTAX INTEGER {
		false(0),
		true(1)
	}
	MAX-ACCESS read-only
	STATUS current
	DESCRIPTION
		"The state indicating whether or not an action will be taken when the
		minimum number of UP members requirement is not met for the specified pool."
	::= { ltmPoolEntry 5 }

ltmPoolMinUpMemberAction OBJECT-TYPE
	SYNTAX INTEGER {
		unusedhaaction(0),
		reboot(1),
		restart(2),
		failover(3),
		goactive(4),
		noaction(5),
		restartall(6),
		failoveraborttm(7),
		gooffline(8),
		goofflinerestart(9),
		goofflineaborttm(10),
		goofflinedownlinks(11),
		goofflinedownlinksrestart(12)
	}
	MAX-ACCESS read-only
	STATUS current
	DESCRIPTION
		"The action to be taken if the minimum number of UP members requirement
		is not met for the specified pool. This is used when
		ltmPoolMinUpMembersEnable is true."
	::= { ltmPoolEntry 6 }

ltmPoolMinActiveMembers OBJECT-TYPE
	SYNTAX INTEGER
	MAX-ACCESS read-only
	STATUS current
	DESCRIPTION
		"The minimum number of active members required for traffic to be sent to
		the specified pool. This feature is used for priority pools. The minimum
		active members take into account both the status of the pool member (up/down)
		as well as the number of connections present on the pool member.
		If the number of active members falls below this given threshold,
		traffic is sent to the next priority pool."
	::= { ltmPoolEntry 7 }

ltmPoolActiveMemberCnt OBJECT-TYPE
	SYNTAX INTEGER
	MAX-ACCESS read-only
	STATUS current
	DESCRIPTION
		"The number of the current active members in the specified pool."
	::= { ltmPoolEntry 8 }

ltmPoolDisallowSnat OBJECT-TYPE
	SYNTAX INTEGER {
		allowed(0),
		disallowed(1)
	}
	MAX-ACCESS read-only
	STATUS current
	DESCRIPTION
		"The state whether SNAT is disallowed or not for the specified pool."
	::= { ltmPoolEntry 9 }

ltmPoolDisallowNat OBJECT-TYPE
	SYNTAX INTEGER {
		allowed(0),
		disallowed(1)
	}
	MAX-ACCESS read-only
	STATUS current
	DESCRIPTION
		"The state whether NAT is disallowed or not for the specified pool."
	::= { ltmPoolEntry 10 }

ltmPoolSimpleTimeout OBJECT-TYPE
	SYNTAX Gauge
	MAX-ACCESS read-only
	STATUS current
	DESCRIPTION
		"The timeout (in seconds) in simple persistence for the specified pool."
	::= { ltmPoolEntry 11 }

ltmPoolIpTosToClient OBJECT-TYPE
	SYNTAX INTEGER
	MAX-ACCESS read-only
	STATUS current
	DESCRIPTION
		"The IP ToS value for client traffic for the specified pool."
	::= { ltmPoolEntry 12 }

ltmPoolIpTosToServer OBJECT-TYPE
	SYNTAX INTEGER
	MAX-ACCESS read-only
	STATUS current
	DESCRIPTION
		"The IP ToS value for server traffic for the specified pool."
	::= { ltmPoolEntry 13 }

ltmPoolLinkQosToClient OBJECT-TYPE
	SYNTAX INTEGER
	MAX-ACCESS read-only
	STATUS current
	DESCRIPTION
		"The link QoS value for client traffic for the specified pool."
	::= { ltmPoolEntry 14 }

ltmPoolLinkQosToServer OBJECT-TYPE
	SYNTAX INTEGER
	MAX-ACCESS read-only
	STATUS current
	DESCRIPTION
		"The link QoS value for server traffic for the specified pool."
	::= { ltmPoolEntry 15 }

ltmPoolDynamicRatioSum OBJECT-TYPE
	SYNTAX Gauge
	MAX-ACCESS read-only
	STATUS current
	DESCRIPTION
		"The sum of the dynamic ratio from all the members of the specified pool."
	::= { ltmPoolEntry 16 }

ltmPoolMonitorRule OBJECT-TYPE
	SYNTAX LongDisplayString
	MAX-ACCESS read-only
	STATUS current
	DESCRIPTION
		"The name of monitor rule used by the specified pool."
	::= { ltmPoolEntry 17 }

ltmPoolAvailabilityState OBJECT-TYPE
	SYNTAX INTEGER {
		none(0),
		green(1),
		yellow(2),
		red(3),
		blue(4)
	}
	MAX-ACCESS read-only
	STATUS	 deprecated
	DESCRIPTION
		"Deprecated!
		Replaced by ltmPooltatusAvailState under ltmPoolStatus.
		The state of the specified pool availability indicated in color."
	::= { ltmPoolEntry 18 }

ltmPoolEnabledState OBJECT-TYPE
	SYNTAX INTEGER {
		none(0),
		enabled(1),
		disabled(2),
		disabledbyparent(3)
	}
	MAX-ACCESS read-only
	STATUS	 deprecated
	DESCRIPTION
		"Deprecated!
		Replaced by ltmPoolStatusEnabledState under ltmPoolStatus.
		The state of the specified pool activity status, as specified by the user."
	::= { ltmPoolEntry 19 }

ltmPoolDisabledParentType OBJECT-TYPE
	SYNTAX Gauge
	MAX-ACCESS read-only
	STATUS	 deprecated
	DESCRIPTION
		"Deprecated!
		Replaced by ltmPoolStatusParentType under ltmPoolStatus.
		The type of parent object which disabled the specified pool."
	::= { ltmPoolEntry 20 }

ltmPoolStatusReason OBJECT-TYPE
	SYNTAX LongDisplayString
	MAX-ACCESS read-only
	STATUS	 deprecated
	DESCRIPTION
		"Deprecated!
		Replaced by ltmPoolStatusDetailReason under ltmPoolStatus.
		The detail description of the pool's status of parent object
		which disabled the specified pool."
	::= { ltmPoolEntry 21 }

ltmPoolSlowRampTime OBJECT-TYPE
	SYNTAX Gauge
	MAX-ACCESS read-only
	STATUS current
	DESCRIPTION
		"The ramp-up time (in seconds) to gradually ramp up the load
		on newly added or freshly detected UP pool members."
	::= { ltmPoolEntry 22 }

ltmPoolMemberCnt OBJECT-TYPE
	SYNTAX Gauge
	MAX-ACCESS read-only
	STATUS current
	DESCRIPTION
		"The total number of members in the specified pool."
	::= { ltmPoolEntry 23 }

ltmPoolQueueOnConnectionLimit OBJECT-TYPE
	SYNTAX INTEGER {
		disabled(0),
		enabled(1)
	}
	MAX-ACCESS read-only
	STATUS current
	DESCRIPTION
		"Enable or disable queuing based on pool member connection limits."
	::= { ltmPoolEntry 24 }

ltmPoolQueueDepthLimit OBJECT-TYPE
	SYNTAX Gauge
	MAX-ACCESS read-only
	STATUS current
	DESCRIPTION
		"Maximum number of connections in queue for pool and all members.
		No limit if unspecified or 0."
	::= { ltmPoolEntry 25 }

ltmPoolQueueTimeLimit OBJECT-TYPE
	SYNTAX Gauge
	MAX-ACCESS read-only
	STATUS current
	DESCRIPTION
		"Maximum number of milliseconds a connection may stay queued.
		No limit if unspecified or 0."
	::= { ltmPoolEntry 26 }

ltmPoolDescription OBJECT-TYPE
	SYNTAX LongDisplayString
	MAX-ACCESS read-only
	STATUS current
	DESCRIPTION
		"The description of the pool."
	::= { ltmPoolEntry 27 }

--==================================================================
-- Pool_stat
--==================================================================
ltmPoolStatResetStats OBJECT-TYPE
	SYNTAX INTEGER
	MAX-ACCESS read-write
	STATUS current
	DESCRIPTION
		"The action to reset resettable statistics data in ltmPoolStat.
		 Setting this value to 1 will reset statistics data.
		 Note, some statistics data may not be reset including data that are incremental counters."
	::= { ltmPoolStat 1 }

ltmPoolStatNumber OBJECT-TYPE
	SYNTAX INTEGER
	MAX-ACCESS read-only
	STATUS current
	DESCRIPTION
		"The number of ltmPoolStat entries in the table."
	::= { ltmPoolStat 2 }

ltmPoolStatTable OBJECT-TYPE
	SYNTAX SEQUENCE OF LtmPoolStatEntry
	MAX-ACCESS not-accessible
	STATUS current
	DESCRIPTION
		"A table containing statistic information of pools."
	::= { ltmPoolStat 3 }

ltmPoolStatEntry OBJECT-TYPE
	SYNTAX  LtmPoolStatEntry
	MAX-ACCESS not-accessible
	STATUS current
	DESCRIPTION
		"Columns in the ltmPoolStat Table"
	INDEX {
		ltmPoolStatName
	}
	::= { ltmPoolStatTable 1 }

LtmPoolStatEntry ::=
	SEQUENCE {
        	ltmPoolStatName                                           LongDisplayString,
        	ltmPoolStatServerPktsIn                                   Counter64,
        	ltmPoolStatServerBytesIn                                  Counter64,
        	ltmPoolStatServerPktsOut                                  Counter64,
        	ltmPoolStatServerBytesOut                                 Counter64,
        	ltmPoolStatServerMaxConns                                 Counter64,
        	ltmPoolStatServerTotConns                                 Counter64,
        	ltmPoolStatServerCurConns                                 Gauge,
        	ltmPoolStatPvaPktsIn                                      Counter64,
        	ltmPoolStatPvaBytesIn                                     Counter64,
        	ltmPoolStatPvaPktsOut                                     Counter64,
        	ltmPoolStatPvaBytesOut                                    Counter64,
        	ltmPoolStatPvaMaxConns                                    Counter64,
        	ltmPoolStatPvaTotConns                                    Counter64,
        	ltmPoolStatPvaCurConns                                    Gauge,
        	ltmPoolStatTotPvaAssistConn                               Counter64,
        	ltmPoolStatCurrPvaAssistConn                              Gauge,
        	ltmPoolStatConnqDepth                                     Gauge,
        	ltmPoolStatConnqAgeHead                                   Gauge,
        	ltmPoolStatConnqAgeMax                                    Gauge,
        	ltmPoolStatConnqAgeEma                                    Gauge,
        	ltmPoolStatConnqAgeEdm                                    Gauge,
        	ltmPoolStatConnqServiced                                  Counter64,
        	ltmPoolStatConnqAllDepth                                  Gauge,
        	ltmPoolStatConnqAllAgeHead                                Gauge,
        	ltmPoolStatConnqAllAgeMax                                 Gauge,
        	ltmPoolStatConnqAllAgeEma                                 Gauge,
        	ltmPoolStatConnqAllAgeEdm                                 Gauge,
        	ltmPoolStatConnqAllServiced                               Counter64,
        	ltmPoolStatTotRequests                                    Counter64,
        	ltmPoolStatCurSessions                                    Gauge,
        	ltmPoolStatMsgMrIn                                        Counter64,
        	ltmPoolStatMsgMrOut                                       Counter64,
        	ltmPoolStatReqMrIn                                        Counter64,
        	ltmPoolStatReqMrOut                                       Counter64,
        	ltmPoolStatRespMrIn                                       Counter64,
        	ltmPoolStatRespMrOut                                      Counter64
	}

ltmPoolStatName OBJECT-TYPE
	SYNTAX LongDisplayString
	MAX-ACCESS read-only
	STATUS current
	DESCRIPTION
		"The name of this pool."
	::= { ltmPoolStatEntry 1 }

ltmPoolStatServerPktsIn OBJECT-TYPE
	SYNTAX Counter64
	MAX-ACCESS read-only
	STATUS current
	DESCRIPTION
		"The number of packets received by the specified pool from server-side."
	::= { ltmPoolStatEntry 2 }

ltmPoolStatServerBytesIn OBJECT-TYPE
	SYNTAX Counter64
	MAX-ACCESS read-only
	STATUS current
	DESCRIPTION
		"The number of bytes received by the specified pool from server-side."
	::= { ltmPoolStatEntry 3 }

ltmPoolStatServerPktsOut OBJECT-TYPE
	SYNTAX Counter64
	MAX-ACCESS read-only
	STATUS current
	DESCRIPTION
		"The number of packets sent to server-side from the specified pool."
	::= { ltmPoolStatEntry 4 }

ltmPoolStatServerBytesOut OBJECT-TYPE
	SYNTAX Counter64
	MAX-ACCESS read-only
	STATUS current
	DESCRIPTION
		"The number of bytes sent to server-side from the specified pool."
	::= { ltmPoolStatEntry 5 }

ltmPoolStatServerMaxConns OBJECT-TYPE
	SYNTAX Counter64
	MAX-ACCESS read-only
	STATUS current
	DESCRIPTION
		"The maximum connections from server-side to the specified pool."
	::= { ltmPoolStatEntry 6 }

ltmPoolStatServerTotConns OBJECT-TYPE
	SYNTAX Counter64
	MAX-ACCESS read-only
	STATUS current
	DESCRIPTION
		"The total connections from server-side to the specified pool."
	::= { ltmPoolStatEntry 7 }

ltmPoolStatServerCurConns OBJECT-TYPE
	SYNTAX Gauge
	MAX-ACCESS read-only
	STATUS current
	DESCRIPTION
		"The current connections from server-side to the specified pool."
	::= { ltmPoolStatEntry 8 }

ltmPoolStatPvaPktsIn OBJECT-TYPE
	SYNTAX Counter64
	MAX-ACCESS read-only
	STATUS current
	DESCRIPTION
		"The number of hardware accelerated packets received by the specified pool."
	::= { ltmPoolStatEntry 9 }

ltmPoolStatPvaBytesIn OBJECT-TYPE
	SYNTAX Counter64
	MAX-ACCESS read-only
	STATUS current
	DESCRIPTION
		"The number of hardware accelerated bytes received by the specified pool."
	::= { ltmPoolStatEntry 10 }

ltmPoolStatPvaPktsOut OBJECT-TYPE
	SYNTAX Counter64
	MAX-ACCESS read-only
	STATUS current
	DESCRIPTION
		"The number of hardware accelerated packets sent out from the specified pool."
	::= { ltmPoolStatEntry 11 }

ltmPoolStatPvaBytesOut OBJECT-TYPE
	SYNTAX Counter64
	MAX-ACCESS read-only
	STATUS current
	DESCRIPTION
		"The number of hardware accelerated bytes sent out from the specified pool."
	::= { ltmPoolStatEntry 12 }

ltmPoolStatPvaMaxConns OBJECT-TYPE
	SYNTAX Counter64
	MAX-ACCESS read-only
	STATUS current
	DESCRIPTION
		"The maximum hardware accelerated connections to the specified pool."
	::= { ltmPoolStatEntry 13 }

ltmPoolStatPvaTotConns OBJECT-TYPE
	SYNTAX Counter64
	MAX-ACCESS read-only
	STATUS current
	DESCRIPTION
		"The total hardware accelerated connections to the specified pool."
	::= { ltmPoolStatEntry 14 }

ltmPoolStatPvaCurConns OBJECT-TYPE
	SYNTAX Gauge
	MAX-ACCESS read-only
	STATUS current
	DESCRIPTION
		"The current hardware accelerated connections to the specified pool."
	::= { ltmPoolStatEntry 15 }

ltmPoolStatTotPvaAssistConn OBJECT-TYPE
	SYNTAX Counter64
	MAX-ACCESS read-only
	STATUS current
	DESCRIPTION
		"The total number of connections to the specified pool,
		which are partially hardware accelerated."
	::= { ltmPoolStatEntry 16 }

ltmPoolStatCurrPvaAssistConn OBJECT-TYPE
	SYNTAX Gauge
	MAX-ACCESS read-only
	STATUS current
	DESCRIPTION
		"The current number of connections to the specified pool,
		which are partially hardware accelerated."
	::= { ltmPoolStatEntry 17 }

ltmPoolStatConnqDepth OBJECT-TYPE
	SYNTAX Gauge
	MAX-ACCESS read-only
	STATUS current
	DESCRIPTION
		"Number of connections currently in queue, sum."
	::= { ltmPoolStatEntry 18 }

ltmPoolStatConnqAgeHead OBJECT-TYPE
	SYNTAX Gauge
	MAX-ACCESS read-only
	STATUS current
	DESCRIPTION
		"Age in milliseconds of the oldest queue entry, max."
	::= { ltmPoolStatEntry 19 }

ltmPoolStatConnqAgeMax OBJECT-TYPE
	SYNTAX Gauge
	MAX-ACCESS read-only
	STATUS current
	DESCRIPTION
		"Maximum queue entry age in milliseconds, max."
	::= { ltmPoolStatEntry 20 }

ltmPoolStatConnqAgeEma OBJECT-TYPE
	SYNTAX Gauge
	MAX-ACCESS read-only
	STATUS current
	DESCRIPTION
		"Exponential moving average queue entry age in milliseconds, max."
	::= { ltmPoolStatEntry 21 }

ltmPoolStatConnqAgeEdm OBJECT-TYPE
	SYNTAX Gauge
	MAX-ACCESS read-only
	STATUS current
	DESCRIPTION
		"Exponential decaying maximum queue entry age in milliseconds, max."
	::= { ltmPoolStatEntry 22 }

ltmPoolStatConnqServiced OBJECT-TYPE
	SYNTAX Counter64
	MAX-ACCESS read-only
	STATUS current
	DESCRIPTION
		"Number of entries that have been removed from the queue, sum."
	::= { ltmPoolStatEntry 23 }

ltmPoolStatConnqAllDepth OBJECT-TYPE
	SYNTAX Gauge
	MAX-ACCESS read-only
	STATUS current
	DESCRIPTION
		"Number of connections currently in queue of this pool and all
		its members, sum."
	::= { ltmPoolStatEntry 24 }

ltmPoolStatConnqAllAgeHead OBJECT-TYPE
	SYNTAX Gauge
	MAX-ACCESS read-only
	STATUS current
	DESCRIPTION
		"Age in milliseconds of the oldest queue entry of this pool and all
		its members, max."
	::= { ltmPoolStatEntry 25 }

ltmPoolStatConnqAllAgeMax OBJECT-TYPE
	SYNTAX Gauge
	MAX-ACCESS read-only
	STATUS current
	DESCRIPTION
		"Maximum queue entry age in milliseconds of this pool and all
		its members, max."
	::= { ltmPoolStatEntry 26 }

ltmPoolStatConnqAllAgeEma OBJECT-TYPE
	SYNTAX Gauge
	MAX-ACCESS read-only
	STATUS current
	DESCRIPTION
		"Exponential moving average queue entry age in milliseconds of this
		pool and all its members, max."
	::= { ltmPoolStatEntry 27 }

ltmPoolStatConnqAllAgeEdm OBJECT-TYPE
	SYNTAX Gauge
	MAX-ACCESS read-only
	STATUS current
	DESCRIPTION
		"Exponential decaying maximum queue entry age in milliseconds of
		this pool and all its members, max."
	::= { ltmPoolStatEntry 28 }

ltmPoolStatConnqAllServiced OBJECT-TYPE
	SYNTAX Counter64
	MAX-ACCESS read-only
	STATUS current
	DESCRIPTION
		"Number of entries that have been removed from the queue of this
		pool and all its members, sum."
	::= { ltmPoolStatEntry 29 }

ltmPoolStatTotRequests OBJECT-TYPE
	SYNTAX Counter64
	MAX-ACCESS read-only
	STATUS current
	DESCRIPTION
		"The total number of requests to the specified pool."
	::= { ltmPoolStatEntry 30 }

ltmPoolStatCurSessions OBJECT-TYPE
	SYNTAX Gauge
	MAX-ACCESS read-only
	STATUS current
	DESCRIPTION
		"The current number of sessions to the specified pool."
	::= { ltmPoolStatEntry 31 }

ltmPoolStatMsgMrIn OBJECT-TYPE
	SYNTAX Counter64
	MAX-ACCESS read-only
	STATUS current
	DESCRIPTION
		"The number of incoming routed messages to the specified pool. "
	::= { ltmPoolStatEntry 32 }

ltmPoolStatMsgMrOut OBJECT-TYPE
	SYNTAX Counter64
	MAX-ACCESS read-only
	STATUS current
	DESCRIPTION
		"The number of outgoing routed messages to the specified pool."
	::= { ltmPoolStatEntry 33 }

ltmPoolStatReqMrIn OBJECT-TYPE
	SYNTAX Counter64
	MAX-ACCESS read-only
	STATUS current
	DESCRIPTION
		"The number of routed message incoming requests to the specified pool."
	::= { ltmPoolStatEntry 34 }

ltmPoolStatReqMrOut OBJECT-TYPE
	SYNTAX Counter64
	MAX-ACCESS read-only
	STATUS current
	DESCRIPTION
		"The number of routed message outgoing requests to the specified pool."
	::= { ltmPoolStatEntry 35 }

ltmPoolStatRespMrIn OBJECT-TYPE
	SYNTAX Counter64
	MAX-ACCESS read-only
	STATUS current
	DESCRIPTION
		"The number of routed message incoming responses to the specified pool."
	::= { ltmPoolStatEntry 36 }

ltmPoolStatRespMrOut OBJECT-TYPE
	SYNTAX Counter64
	MAX-ACCESS read-only
	STATUS current
	DESCRIPTION
		"The number of routed message outgoing responses to the specified pool."
	::= { ltmPoolStatEntry 37 }

--==================================================================
-- Pool_member
--==================================================================
ltmPoolMemberNumber OBJECT-TYPE
	SYNTAX INTEGER
	MAX-ACCESS read-only
	STATUS current
	DESCRIPTION
		"The number of ltmPoolMember entries in the table."
	::= { ltmPoolMember 1 }

ltmPoolMemberTable OBJECT-TYPE
	SYNTAX SEQUENCE OF LtmPoolMemberEntry
	MAX-ACCESS not-accessible
	STATUS current
	DESCRIPTION
		"A table containing information of pool members."
	::= { ltmPoolMember 2 }

ltmPoolMemberEntry OBJECT-TYPE
	SYNTAX  LtmPoolMemberEntry
	MAX-ACCESS not-accessible
	STATUS current
	DESCRIPTION
		"Columns in the ltmPoolMember Table"
	INDEX {
		ltmPoolMemberPoolName,
		ltmPoolMemberNodeName,
		ltmPoolMemberPort
	}
	::= { ltmPoolMemberTable 1 }

LtmPoolMemberEntry ::=
	SEQUENCE {
        	ltmPoolMemberPoolName                                     LongDisplayString,
        	ltmPoolMemberAddrType                                     InetAddressType,
        	ltmPoolMemberAddr                                         InetAddress,
        	ltmPoolMemberPort                                         InetPortNumber,
        	ltmPoolMemberConnLimit                                    Gauge,
        	ltmPoolMemberRatio                                        Gauge,
        	ltmPoolMemberWeight                                       INTEGER,
        	ltmPoolMemberPriority                                     INTEGER,
        	ltmPoolMemberDynamicRatio                                 INTEGER,
        	ltmPoolMemberMonitorState                                 INTEGER,
        	ltmPoolMemberMonitorStatus                                INTEGER,
        	ltmPoolMemberNewSessionEnable                             INTEGER,
        	ltmPoolMemberSessionStatus                                INTEGER,
        	ltmPoolMemberMonitorRule                                  LongDisplayString,
        	ltmPoolMemberAvailabilityState                            INTEGER,
        	ltmPoolMemberEnabledState                                 INTEGER,
        	ltmPoolMemberDisabledParentType                           Gauge,
        	ltmPoolMemberStatusReason                                 LongDisplayString,
        	ltmPoolMemberNodeName                                     LongDisplayString
	}

ltmPoolMemberPoolName OBJECT-TYPE
	SYNTAX LongDisplayString
	MAX-ACCESS read-only
	STATUS current
	DESCRIPTION
		"The name of a pool."
	::= { ltmPoolMemberEntry 1 }

ltmPoolMemberAddrType OBJECT-TYPE
	SYNTAX InetAddressType
	MAX-ACCESS read-only
	STATUS current
	DESCRIPTION
		"The IP address type of ltmPoolMemberAddr."
	::= { ltmPoolMemberEntry 2 }

ltmPoolMemberAddr OBJECT-TYPE
	SYNTAX InetAddress
	MAX-ACCESS read-only
	STATUS current
	DESCRIPTION
		"The IP address of a pool member in the specified pool.
		It is interpreted within the context of an ltmPoolMemberAddrType value."
	::= { ltmPoolMemberEntry 3 }

ltmPoolMemberPort OBJECT-TYPE
	SYNTAX InetPortNumber
	MAX-ACCESS read-only
	STATUS current
	DESCRIPTION
		"The port number of the specified pool member."
	::= { ltmPoolMemberEntry 4 }

ltmPoolMemberConnLimit OBJECT-TYPE
	SYNTAX Gauge
	MAX-ACCESS read-only
	STATUS current
	DESCRIPTION
		"The maximum connections allowed to the specified pool member."
	::= { ltmPoolMemberEntry 5 }

ltmPoolMemberRatio OBJECT-TYPE
	SYNTAX Gauge
	MAX-ACCESS read-only
	STATUS current
	DESCRIPTION
		"The load balancing ratio of the specified pool member,
		used in pool member ratio load balancing mode."
	::= { ltmPoolMemberEntry 6 }

ltmPoolMemberWeight OBJECT-TYPE
	SYNTAX INTEGER
	MAX-ACCESS read-only
	STATUS current
	DESCRIPTION
		"The weight of the specified pool member, used in dynamic load balancing mode."
	::= { ltmPoolMemberEntry 7 }

ltmPoolMemberPriority OBJECT-TYPE
	SYNTAX INTEGER
	MAX-ACCESS read-only
	STATUS current
	DESCRIPTION
		"The priority level of the specified pool member,
		used in priority pool member load balancing mode."
	::= { ltmPoolMemberEntry 8 }

ltmPoolMemberDynamicRatio OBJECT-TYPE
	SYNTAX INTEGER
	MAX-ACCESS read-only
	STATUS current
	DESCRIPTION
		"The dynamic ratio for the specified pool member, used in load balance
		 algorithm."
	::= { ltmPoolMemberEntry 9 }

ltmPoolMemberMonitorState OBJECT-TYPE
	SYNTAX INTEGER {
		unchecked(0),
		checking(1),
		inband(2),
		forcedUp(3),
		up(4),
		down(19),
		forcedDown(20),
		iruleDown(22),
		inbandDown(23),
		downManualResume(24),
		disabled(25)
	}
	MAX-ACCESS read-write
	STATUS current
	DESCRIPTION
		"The internal tmm monitor state for the specified node address."
	::= { ltmPoolMemberEntry 10 }

ltmPoolMemberMonitorStatus OBJECT-TYPE
	SYNTAX INTEGER {
		unchecked(0),
		checking(1),
		inband(2),
		forcedUp(3),
		up(4),
		addrDown(18),
		down(19),
		forcedDown(20),
		maint(21),
		iruleDown(22),
		inbandDown(23),
		downManualResume(24)
	}
	MAX-ACCESS read-only
	STATUS current
	DESCRIPTION
		"The hierarchical load balance state for the specified node address, including parent status.
		 unchecked - enabled node that is not monitored;
		 checking  - initial state until monitor reports;
	         inband    - the tmm has marked the node up;
	     forcedUp - forced up manually;
		 up        - enabled node when its monitors succeed;
		 addrDown    - node address monitor fails or forced down;
		 down        - enabled node when its monitors fail;
		 forcedDown  - node forced down manually;
		 maint       - in maintenance mode;
	         iruleDown   - an iRule has marked the node down;
	         inbandDown  - the tmm has marked the node down;
	         downManualResume - the node is down and must be manually enabled;
		 "
	::= { ltmPoolMemberEntry 11 }

ltmPoolMemberNewSessionEnable OBJECT-TYPE
	SYNTAX INTEGER {
		userDisabled(1),
		userEnabled(2),
		monitorEnabled(3),
		monitorDisabled(4)
	}
	MAX-ACCESS read-only
	STATUS	 deprecated
	DESCRIPTION
		"Deprecated!
		 Whether a new session can be enabled or not for the specified pool member."
	::= { ltmPoolMemberEntry 12 }

ltmPoolMemberSessionStatus OBJECT-TYPE
	SYNTAX INTEGER {
		enabled(1),
		addrdisabled(2),
		servdisabled(3),
		disabled(4),
		forceddisabled(5)
	}
	MAX-ACCESS read-only
	STATUS current
	DESCRIPTION
		"The hierarchical status of the session, including parent status,
		for the specified pool member.
		enabled        - new sessions enabled;
		addrdisabled   - new sessions disabled on node address;
		servdisabled   - new sessions disabled on node server;
		disabled       - new sessions disabled;
		forceddisabled - new sessions forced to be disabled."
	::= { ltmPoolMemberEntry 13 }

ltmPoolMemberMonitorRule OBJECT-TYPE
	SYNTAX LongDisplayString
	MAX-ACCESS read-only
	STATUS current
	DESCRIPTION
		"The monitor rule used by the specified pool member.
		If this value is empty, ltmPoolMonitorRule will be used."
	::= { ltmPoolMemberEntry 14 }

ltmPoolMemberAvailabilityState OBJECT-TYPE
	SYNTAX INTEGER {
		none(0),
		green(1),
		yellow(2),
		red(3),
		blue(4)
	}
	MAX-ACCESS read-only
	STATUS	 deprecated
	DESCRIPTION
		"Deprecated!
		Replaced by ltmPoolMbrStatusAvailState under ltmPoolMemberStatus.
		The state of the specified pool member availability indicated in color."
	::= { ltmPoolMemberEntry 15 }

ltmPoolMemberEnabledState OBJECT-TYPE
	SYNTAX INTEGER {
		none(0),
		enabled(1),
		disabled(2),
		disabledbyparent(3)
	}
	MAX-ACCESS read-only
	STATUS	 deprecated
	DESCRIPTION
		"Deprecated!
		Replaced by ltmPoolMbrStatusEnabledState under ltmPoolMemberStatus.
		The state of the specified pool member activity status, as specified
		by the user."
	::= { ltmPoolMemberEntry 16 }

ltmPoolMemberDisabledParentType OBJECT-TYPE
	SYNTAX Gauge
	MAX-ACCESS read-only
	STATUS	 deprecated
	DESCRIPTION
		"Deprecated!
		Replaced by ltmPoolMbrStatusParentType under ltmPoolMemberStatus.
		The type of parent object which disabled the specified pool member."
	::= { ltmPoolMemberEntry 17 }

ltmPoolMemberStatusReason OBJECT-TYPE
	SYNTAX LongDisplayString
	MAX-ACCESS read-only
	STATUS	 deprecated
	DESCRIPTION
		"Deprecated!
		Replaced by ltmPoolMbrStatusDetailReason under ltmPoolMemberStatus.
		The detail description of the pool member's status of parent object
		which disabled the specified pool member."
	::= { ltmPoolMemberEntry 18 }

ltmPoolMemberNodeName OBJECT-TYPE
	SYNTAX LongDisplayString
	MAX-ACCESS read-only
	STATUS current
	DESCRIPTION
		"Name of associated name."
	::= { ltmPoolMemberEntry 19 }

--==================================================================
-- Pool_member_stat
--==================================================================
ltmPoolMemberStatResetStats OBJECT-TYPE
	SYNTAX INTEGER
	MAX-ACCESS read-write
	STATUS current
	DESCRIPTION
		"The action to reset resettable statistics data in ltmPoolMemberStat.
		 Setting this value to 1 will reset statistics data.
		 Note, some statistics data may not be reset including data that are incremental counters."
	::= { ltmPoolMemberStat 1 }

ltmPoolMemberStatNumber OBJECT-TYPE
	SYNTAX INTEGER
	MAX-ACCESS read-only
	STATUS current
	DESCRIPTION
		"The number of ltmPoolMemberStat entries in the table."
	::= { ltmPoolMemberStat 2 }

ltmPoolMemberStatTable OBJECT-TYPE
	SYNTAX SEQUENCE OF LtmPoolMemberStatEntry
	MAX-ACCESS not-accessible
	STATUS current
	DESCRIPTION
		"A table containing statistic information of pool members."
	::= { ltmPoolMemberStat 3 }

ltmPoolMemberStatEntry OBJECT-TYPE
	SYNTAX  LtmPoolMemberStatEntry
	MAX-ACCESS not-accessible
	STATUS current
	DESCRIPTION
		"Columns in the ltmPoolMemberStat Table"
	INDEX {
		ltmPoolMemberStatPoolName,
		ltmPoolMemberStatNodeName,
		ltmPoolMemberStatPort
	}
	::= { ltmPoolMemberStatTable 1 }

LtmPoolMemberStatEntry ::=
	SEQUENCE {
        	ltmPoolMemberStatPoolName                                 LongDisplayString,
        	ltmPoolMemberStatAddrType                                 InetAddressType,
        	ltmPoolMemberStatAddr                                     InetAddress,
        	ltmPoolMemberStatPort                                     InetPortNumber,
        	ltmPoolMemberStatServerPktsIn                             Counter64,
        	ltmPoolMemberStatServerBytesIn                            Counter64,
        	ltmPoolMemberStatServerPktsOut                            Counter64,
        	ltmPoolMemberStatServerBytesOut                           Counter64,
        	ltmPoolMemberStatServerMaxConns                           Counter64,
        	ltmPoolMemberStatServerTotConns                           Counter64,
        	ltmPoolMemberStatServerCurConns                           Gauge,
        	ltmPoolMemberStatPvaPktsIn                                Counter64,
        	ltmPoolMemberStatPvaBytesIn                               Counter64,
        	ltmPoolMemberStatPvaPktsOut                               Counter64,
        	ltmPoolMemberStatPvaBytesOut                              Counter64,
        	ltmPoolMemberStatPvaMaxConns                              Counter64,
        	ltmPoolMemberStatPvaTotConns                              Counter64,
        	ltmPoolMemberStatPvaCurConns                              Gauge,
        	ltmPoolMemberStatTotRequests                              Counter64,
        	ltmPoolMemberStatTotPvaAssistConn                         Counter64,
        	ltmPoolMemberStatCurrPvaAssistConn                        Gauge,
        	ltmPoolMemberStatConnqDepth                               Gauge,
        	ltmPoolMemberStatConnqAgeHead                             Gauge,
        	ltmPoolMemberStatConnqAgeMax                              Gauge,
        	ltmPoolMemberStatConnqAgeEma                              Gauge,
        	ltmPoolMemberStatConnqAgeEdm                              Gauge,
        	ltmPoolMemberStatConnqServiced                            Counter64,
        	ltmPoolMemberStatNodeName                                 LongDisplayString,
        	ltmPoolMemberStatCurSessions                              Gauge,
        	ltmPoolMemberStatCurrentConnsPerSec                       Gauge,
        	ltmPoolMemberStatDurationRateExceeded                     Gauge,
        	ltmPoolMemberStatMsgMrIn                                  Counter64,
        	ltmPoolMemberStatMsgMrOut                                 Counter64,
        	ltmPoolMemberStatReqMrIn                                  Counter64,
        	ltmPoolMemberStatReqMrOut                                 Counter64,
        	ltmPoolMemberStatRespMrIn                                 Counter64,
        	ltmPoolMemberStatRespMrOut                                Counter64
	}

ltmPoolMemberStatPoolName OBJECT-TYPE
	SYNTAX LongDisplayString
	MAX-ACCESS read-only
	STATUS current
	DESCRIPTION
		"The name of a pool."
	::= { ltmPoolMemberStatEntry 1 }

ltmPoolMemberStatAddrType OBJECT-TYPE
	SYNTAX InetAddressType
	MAX-ACCESS read-only
	STATUS	 deprecated
	DESCRIPTION
		"Deprecated! use node_name instead,
		The IP address type of ltmPoolMemberStatAddr."
	::= { ltmPoolMemberStatEntry 2 }

ltmPoolMemberStatAddr OBJECT-TYPE
	SYNTAX InetAddress
	MAX-ACCESS read-only
	STATUS	 deprecated
	DESCRIPTION
		"Deprecated! use node_name instead,
		The IP address of a pool member in the specified pool.
		It is interpreted within the context of an ltmPoolMemberStatAddrType value."
	::= { ltmPoolMemberStatEntry 3 }

ltmPoolMemberStatPort OBJECT-TYPE
	SYNTAX InetPortNumber
	MAX-ACCESS read-only
	STATUS current
	DESCRIPTION
		"The port number of the specified pool member."
	::= { ltmPoolMemberStatEntry 4 }

ltmPoolMemberStatServerPktsIn OBJECT-TYPE
	SYNTAX Counter64
	MAX-ACCESS read-only
	STATUS current
	DESCRIPTION
		"The number of packets received by the specified pool member from server-side."
	::= { ltmPoolMemberStatEntry 5 }

ltmPoolMemberStatServerBytesIn OBJECT-TYPE
	SYNTAX Counter64
	MAX-ACCESS read-only
	STATUS current
	DESCRIPTION
		"The number of bytes received by the specified pool member from server-side."
	::= { ltmPoolMemberStatEntry 6 }

ltmPoolMemberStatServerPktsOut OBJECT-TYPE
	SYNTAX Counter64
	MAX-ACCESS read-only
	STATUS current
	DESCRIPTION
		"The number of packets sent to server-side from the specified pool member."
	::= { ltmPoolMemberStatEntry 7 }

ltmPoolMemberStatServerBytesOut OBJECT-TYPE
	SYNTAX Counter64
	MAX-ACCESS read-only
	STATUS current
	DESCRIPTION
		"The number of bytes sent to server-side from the specified pool member."
	::= { ltmPoolMemberStatEntry 8 }

ltmPoolMemberStatServerMaxConns OBJECT-TYPE
	SYNTAX Counter64
	MAX-ACCESS read-only
	STATUS current
	DESCRIPTION
		"The maximum connections from server-side to the specified pool member."
	::= { ltmPoolMemberStatEntry 9 }

ltmPoolMemberStatServerTotConns OBJECT-TYPE
	SYNTAX Counter64
	MAX-ACCESS read-only
	STATUS current
	DESCRIPTION
		"The total connections from server-side to the specified pool member."
	::= { ltmPoolMemberStatEntry 10 }

ltmPoolMemberStatServerCurConns OBJECT-TYPE
	SYNTAX Gauge
	MAX-ACCESS read-only
	STATUS current
	DESCRIPTION
		"The current connections from server-side to the pool member."
	::= { ltmPoolMemberStatEntry 11 }

ltmPoolMemberStatPvaPktsIn OBJECT-TYPE
	SYNTAX Counter64
	MAX-ACCESS read-only
	STATUS current
	DESCRIPTION
		"The total number of hardware accelerated packets received by the specified pool member."
	::= { ltmPoolMemberStatEntry 12 }

ltmPoolMemberStatPvaBytesIn OBJECT-TYPE
	SYNTAX Counter64
	MAX-ACCESS read-only
	STATUS current
	DESCRIPTION
		"The total number of hardware accelerated bytes received by the specified pool member."
	::= { ltmPoolMemberStatEntry 13 }

ltmPoolMemberStatPvaPktsOut OBJECT-TYPE
	SYNTAX Counter64
	MAX-ACCESS read-only
	STATUS current
	DESCRIPTION
		"The total number of hardware accelerated packets sent out from the specified pool member."
	::= { ltmPoolMemberStatEntry 14 }

ltmPoolMemberStatPvaBytesOut OBJECT-TYPE
	SYNTAX Counter64
	MAX-ACCESS read-only
	STATUS current
	DESCRIPTION
		"The total number of hardware accelerated bytes sent out from the specified pool member."
	::= { ltmPoolMemberStatEntry 15 }

ltmPoolMemberStatPvaMaxConns OBJECT-TYPE
	SYNTAX Counter64
	MAX-ACCESS read-only
	STATUS current
	DESCRIPTION
		"The maximum hardware accelerated connections to the specified pool member."
	::= { ltmPoolMemberStatEntry 16 }

ltmPoolMemberStatPvaTotConns OBJECT-TYPE
	SYNTAX Counter64
	MAX-ACCESS read-only
	STATUS current
	DESCRIPTION
		"The total hardware accelerated connections to the specified pool member."
	::= { ltmPoolMemberStatEntry 17 }

ltmPoolMemberStatPvaCurConns OBJECT-TYPE
	SYNTAX Gauge
	MAX-ACCESS read-only
	STATUS current
	DESCRIPTION
		"The current hardware accelerated connections to the specified pool member."
	::= { ltmPoolMemberStatEntry 18 }

ltmPoolMemberStatTotRequests OBJECT-TYPE
	SYNTAX Counter64
	MAX-ACCESS read-only
	STATUS current
	DESCRIPTION
		"The total number of requests going through the specified pool member."
	::= { ltmPoolMemberStatEntry 19 }

ltmPoolMemberStatTotPvaAssistConn OBJECT-TYPE
	SYNTAX Counter64
	MAX-ACCESS read-only
	STATUS current
	DESCRIPTION
		"The total number of connections to the specified pool member,
		which are partially hardware accelerated."
	::= { ltmPoolMemberStatEntry 20 }

ltmPoolMemberStatCurrPvaAssistConn OBJECT-TYPE
	SYNTAX Gauge
	MAX-ACCESS read-only
	STATUS current
	DESCRIPTION
		"The current number of connections to the specified pool member,
		which are partially hardware accelerated."
	::= { ltmPoolMemberStatEntry 21 }

ltmPoolMemberStatConnqDepth OBJECT-TYPE
	SYNTAX Gauge
	MAX-ACCESS read-only
	STATUS current
	DESCRIPTION
		"Number of connections currently in queue, sum."
	::= { ltmPoolMemberStatEntry 22 }

ltmPoolMemberStatConnqAgeHead OBJECT-TYPE
	SYNTAX Gauge
	MAX-ACCESS read-only
	STATUS current
	DESCRIPTION
		"Age in milliseconds of the oldest queue entry, max."
	::= { ltmPoolMemberStatEntry 23 }

ltmPoolMemberStatConnqAgeMax OBJECT-TYPE
	SYNTAX Gauge
	MAX-ACCESS read-only
	STATUS current
	DESCRIPTION
		"Maximum queue entry age in milliseconds, max."
	::= { ltmPoolMemberStatEntry 24 }

ltmPoolMemberStatConnqAgeEma OBJECT-TYPE
	SYNTAX Gauge
	MAX-ACCESS read-only
	STATUS current
	DESCRIPTION
		"Exponential moving average queue entry age in milliseconds, max."
	::= { ltmPoolMemberStatEntry 25 }

ltmPoolMemberStatConnqAgeEdm OBJECT-TYPE
	SYNTAX Gauge
	MAX-ACCESS read-only
	STATUS current
	DESCRIPTION
		"Exponential decaying maximum queue entry age in milliseconds, max."
	::= { ltmPoolMemberStatEntry 26 }

ltmPoolMemberStatConnqServiced OBJECT-TYPE
	SYNTAX Counter64
	MAX-ACCESS read-only
	STATUS current
	DESCRIPTION
		"Number of entries that have been removed from the queue, sum."
	::= { ltmPoolMemberStatEntry 27 }

ltmPoolMemberStatNodeName OBJECT-TYPE
	SYNTAX LongDisplayString
	MAX-ACCESS read-only
	STATUS current
	DESCRIPTION
		"node name."
	::= { ltmPoolMemberStatEntry 28 }

ltmPoolMemberStatCurSessions OBJECT-TYPE
	SYNTAX Gauge
	MAX-ACCESS read-only
	STATUS current
	DESCRIPTION
		"The number of current sessions going through the specified pool member."
	::= { ltmPoolMemberStatEntry 29 }

ltmPoolMemberStatCurrentConnsPerSec OBJECT-TYPE
	SYNTAX Gauge
	MAX-ACCESS read-only
	STATUS current
	DESCRIPTION
		"The last recorded value for the number of connections to the pool member when connections hit a rate limit; this calculation is only maintained if rate limiting is configured for the pool member node."
	::= { ltmPoolMemberStatEntry 30 }

ltmPoolMemberStatDurationRateExceeded OBJECT-TYPE
	SYNTAX Gauge
	MAX-ACCESS read-only
	STATUS current
	DESCRIPTION
		"Duration of time in seconds the specified pool member has exceeded the
		configured connection rate limit."
	::= { ltmPoolMemberStatEntry 31 }

ltmPoolMemberStatMsgMrIn OBJECT-TYPE
	SYNTAX Counter64
	MAX-ACCESS read-only
	STATUS current
	DESCRIPTION
		"The number of incoming routed messages to the specified pool member."
	::= { ltmPoolMemberStatEntry 32 }

ltmPoolMemberStatMsgMrOut OBJECT-TYPE
	SYNTAX Counter64
	MAX-ACCESS read-only
	STATUS current
	DESCRIPTION
		"The number of outgoing routed messages to the specified pool member."
	::= { ltmPoolMemberStatEntry 33 }

ltmPoolMemberStatReqMrIn OBJECT-TYPE
	SYNTAX Counter64
	MAX-ACCESS read-only
	STATUS current
	DESCRIPTION
		"The number of routed message incoming requests to the specified pool member."
	::= { ltmPoolMemberStatEntry 34 }

ltmPoolMemberStatReqMrOut OBJECT-TYPE
	SYNTAX Counter64
	MAX-ACCESS read-only
	STATUS current
	DESCRIPTION
		"The number of routed message outgoing requests to the specified pool member."
	::= { ltmPoolMemberStatEntry 35 }

ltmPoolMemberStatRespMrIn OBJECT-TYPE
	SYNTAX Counter64
	MAX-ACCESS read-only
	STATUS current
	DESCRIPTION
		"The number of routed message incoming responses to the specified pool member."
	::= { ltmPoolMemberStatEntry 36 }

ltmPoolMemberStatRespMrOut OBJECT-TYPE
	SYNTAX Counter64
	MAX-ACCESS read-only
	STATUS current
	DESCRIPTION
		"The number of routed message outgoing responses to the specified pool member."
	::= { ltmPoolMemberStatEntry 37 }

--==================================================================
-- Profile_auth
--==================================================================
ltmAuthProfileNumber OBJECT-TYPE
	SYNTAX INTEGER
	MAX-ACCESS read-only
	STATUS current
	DESCRIPTION
		"The number of ltmAuthProfile entries in the table."
	::= { ltmAuthProfile 1 }

ltmAuthProfileTable OBJECT-TYPE
	SYNTAX SEQUENCE OF LtmAuthProfileEntry
	MAX-ACCESS not-accessible
	STATUS current
	DESCRIPTION
		"A table containing information of BIGIP authentication profiles."
	::= { ltmAuthProfile 2 }

ltmAuthProfileEntry OBJECT-TYPE
	SYNTAX  LtmAuthProfileEntry
	MAX-ACCESS not-accessible
	STATUS current
	DESCRIPTION
		"Columns in the ltmAuthProfile Table"
	INDEX {
		ltmAuthProfileName
	}
	::= { ltmAuthProfileTable 1 }

LtmAuthProfileEntry ::=
	SEQUENCE {
        	ltmAuthProfileName                                        LongDisplayString,
        	ltmAuthProfileConfigSource                                INTEGER,
        	ltmAuthProfileDefaultName                                 LongDisplayString,
        	ltmAuthProfileConfigName                                  LongDisplayString,
        	ltmAuthProfileType                                        INTEGER,
        	ltmAuthProfileMode                                        INTEGER,
        	ltmAuthProfileCredentialSource                            INTEGER,
        	ltmAuthProfileRuleName                                    LongDisplayString,
        	ltmAuthProfileIdleTimeout                                 Gauge
	}

ltmAuthProfileName OBJECT-TYPE
	SYNTAX LongDisplayString
	MAX-ACCESS read-only
	STATUS current
	DESCRIPTION
		"The name of an authentication profile."
	::= { ltmAuthProfileEntry 1 }

ltmAuthProfileConfigSource OBJECT-TYPE
	SYNTAX INTEGER {
		usercfg(0),
		basecfg(1)
	}
	MAX-ACCESS read-only
	STATUS current
	DESCRIPTION
		"The state that specifies whether this is a base/pre-configured profile
		or user defined profile."
	::= { ltmAuthProfileEntry 2 }

ltmAuthProfileDefaultName OBJECT-TYPE
	SYNTAX LongDisplayString
	MAX-ACCESS read-only
	STATUS current
	DESCRIPTION
		"The name of the profile from which the specified profile derives
		its attribute default values."
	::= { ltmAuthProfileEntry 3 }

ltmAuthProfileConfigName OBJECT-TYPE
	SYNTAX LongDisplayString
	MAX-ACCESS read-only
	STATUS current
	DESCRIPTION
		"The name of the authentication configuration that the specified
		profile will be using."
	::= { ltmAuthProfileEntry 4 }

ltmAuthProfileType OBJECT-TYPE
	SYNTAX INTEGER {
		ldap(0),
		radius(1),
		sslccldap(2),
		sslocsp(3),
		tacacs(4),
		generic(5),
		sslcrldp(6),
		krbdelegate(7)
	}
	MAX-ACCESS read-only
	STATUS current
	DESCRIPTION
		"The authentication type that the specified profile will be using."
	::= { ltmAuthProfileEntry 5 }

ltmAuthProfileMode OBJECT-TYPE
	SYNTAX INTEGER {
		disabled(0),
		enabled(1)
	}
	MAX-ACCESS read-only
	STATUS current
	DESCRIPTION
		"The mode for the specified auth profile."
	::= { ltmAuthProfileEntry 6 }

ltmAuthProfileCredentialSource OBJECT-TYPE
	SYNTAX INTEGER {
		httpbasicauth(0)
	}
	MAX-ACCESS read-only
	STATUS current
	DESCRIPTION
		"The source of the credentials that the specified profile will be using."
	::= { ltmAuthProfileEntry 7 }

ltmAuthProfileRuleName OBJECT-TYPE
	SYNTAX LongDisplayString
	MAX-ACCESS read-only
	STATUS current
	DESCRIPTION
		"The name of the rule that the specified profile will be using."
	::= { ltmAuthProfileEntry 8 }

ltmAuthProfileIdleTimeout OBJECT-TYPE
	SYNTAX Gauge
	MAX-ACCESS read-only
	STATUS current
	DESCRIPTION
		"The idle timeout in seconds for the authentication session."
	::= { ltmAuthProfileEntry 9 }

--==================================================================
-- Profile_auth_stat
--==================================================================
ltmAuthProfileStatResetStats OBJECT-TYPE
	SYNTAX INTEGER
	MAX-ACCESS read-write
	STATUS current
	DESCRIPTION
		"The action to reset resettable statistics data in ltmAuthProfileStat.
		 Setting this value to 1 will reset statistics data.
		 Note, some statistics data may not be reset including data that are incremental counters."
	::= { ltmAuthProfileStat 1 }

ltmAuthProfileStatNumber OBJECT-TYPE
	SYNTAX INTEGER
	MAX-ACCESS read-only
	STATUS current
	DESCRIPTION
		"The number of ltmAuthProfileStat entries in the table."
	::= { ltmAuthProfileStat 2 }

ltmAuthProfileStatTable OBJECT-TYPE
	SYNTAX SEQUENCE OF LtmAuthProfileStatEntry
	MAX-ACCESS not-accessible
	STATUS current
	DESCRIPTION
		"A table containing statistic information of BIGIP authentication profiles."
	::= { ltmAuthProfileStat 3 }

ltmAuthProfileStatEntry OBJECT-TYPE
	SYNTAX  LtmAuthProfileStatEntry
	MAX-ACCESS not-accessible
	STATUS current
	DESCRIPTION
		"Columns in the ltmAuthProfileStat Table"
	INDEX {
		ltmAuthProfileStatName
	}
	::= { ltmAuthProfileStatTable 1 }

LtmAuthProfileStatEntry ::=
	SEQUENCE {
        	ltmAuthProfileStatName                                    LongDisplayString,
        	ltmAuthProfileStatTotSessions                             Counter64,
        	ltmAuthProfileStatCurSessions                             Gauge,
        	ltmAuthProfileStatMaxSessions                             Counter64,
        	ltmAuthProfileStatSuccessResults                          Counter64,
        	ltmAuthProfileStatFailureResults                          Counter64,
        	ltmAuthProfileStatWantcredentialResults                   Counter64,
        	ltmAuthProfileStatErrorResults                            Counter64
	}

ltmAuthProfileStatName OBJECT-TYPE
	SYNTAX LongDisplayString
	MAX-ACCESS read-only
	STATUS current
	DESCRIPTION
		"The name of an authentication profile."
	::= { ltmAuthProfileStatEntry 1 }

ltmAuthProfileStatTotSessions OBJECT-TYPE
	SYNTAX Counter64
	MAX-ACCESS read-only
	STATUS current
	DESCRIPTION
		"The total number of concurrent auth sessions for the specified profile."
	::= { ltmAuthProfileStatEntry 2 }

ltmAuthProfileStatCurSessions OBJECT-TYPE
	SYNTAX Gauge
	MAX-ACCESS read-only
	STATUS current
	DESCRIPTION
		"The current number of concurrent auth sessions for the specified profile."
	::= { ltmAuthProfileStatEntry 3 }

ltmAuthProfileStatMaxSessions OBJECT-TYPE
	SYNTAX Counter64
	MAX-ACCESS read-only
	STATUS current
	DESCRIPTION
		"The maximum number of concurrent auth sessions for the specified profile"
	::= { ltmAuthProfileStatEntry 4 }

ltmAuthProfileStatSuccessResults OBJECT-TYPE
	SYNTAX Counter64
	MAX-ACCESS read-only
	STATUS current
	DESCRIPTION
		"The total number of auth success results (That is when a
		successful authorization has completed all of the required
		auth services.) for the specified profile."
	::= { ltmAuthProfileStatEntry 5 }

ltmAuthProfileStatFailureResults OBJECT-TYPE
	SYNTAX Counter64
	MAX-ACCESS read-only
	STATUS current
	DESCRIPTION
		"The total number of auth failure results (That is when an
		unsuccessful authorization operation has completed.) for the associated
		virtual server for the specified profile."
	::= { ltmAuthProfileStatEntry 6 }

ltmAuthProfileStatWantcredentialResults OBJECT-TYPE
	SYNTAX Counter64
	MAX-ACCESS read-only
	STATUS current
	DESCRIPTION
		"The total number of auth wantcredential results (That is when
		an authorization operation needs an additional credential.)
		for the specified profile."
	::= { ltmAuthProfileStatEntry 7 }

ltmAuthProfileStatErrorResults OBJECT-TYPE
	SYNTAX Counter64
	MAX-ACCESS read-only
	STATUS current
	DESCRIPTION
		"The total number of auth error results (That is when an error
		occurred during authorization has occurred.) for the specified profile."
	::= { ltmAuthProfileStatEntry 8 }

--==================================================================
-- Profile_clientssl
--==================================================================
ltmClientSslNumber OBJECT-TYPE
	SYNTAX INTEGER
	MAX-ACCESS read-only
	STATUS current
	DESCRIPTION
		"The number of ltmClientSslProfile entries in the table."
	::= { ltmClientSslProfile 1 }

ltmClientSslTable OBJECT-TYPE
	SYNTAX SEQUENCE OF LtmClientSslEntry
	MAX-ACCESS not-accessible
	STATUS current
	DESCRIPTION
		"A table containing information of the client-side SSL profiles.(BIG-IP acts as an SSL server)"
	::= { ltmClientSslProfile 2 }

ltmClientSslEntry OBJECT-TYPE
	SYNTAX  LtmClientSslEntry
	MAX-ACCESS not-accessible
	STATUS current
	DESCRIPTION
		"Columns in the ltmClientSsl Table"
	INDEX {
		ltmClientSslName
	}
	::= { ltmClientSslTable 1 }

LtmClientSslEntry ::=
	SEQUENCE {
        	ltmClientSslName                                          LongDisplayString,
        	ltmClientSslConfigSource                                  INTEGER,
        	ltmClientSslDefaultName                                   LongDisplayString,
        	ltmClientSslMode                                          INTEGER,
        	ltmClientSslKey                                           LongDisplayString,
        	ltmClientSslCert                                          LongDisplayString,
        	ltmClientSslChain                                         LongDisplayString,
        	ltmClientSslCafile                                        LongDisplayString,
        	ltmClientSslCrlfile                                       LongDisplayString,
        	ltmClientSslClientcertca                                  LongDisplayString,
        	ltmClientSslCiphers                                       LongDisplayString,
        	ltmClientSslPassphrase                                    LongDisplayString,
        	ltmClientSslOptions                                       Gauge,
        	ltmClientSslModsslmethods                                 INTEGER,
        	ltmClientSslCacheSize                                     Gauge,
        	ltmClientSslCacheTimeout                                  Gauge,
        	ltmClientSslRenegotiatePeriod                             Gauge,
        	ltmClientSslRenegotiateSize                               Gauge,
        	ltmClientSslRenegotiateMaxRecordDelay                     Gauge,
        	ltmClientSslHandshakeTimeout                              Gauge,
        	ltmClientSslAlertTimeout                                  Gauge,
        	ltmClientSslPeerCertMode                                  INTEGER,
        	ltmClientSslAuthenticateOnce                              INTEGER,
        	ltmClientSslAuthenticateDepth                             Gauge,
        	ltmClientSslUncleanShutdown                               INTEGER,
        	ltmClientSslStrictResume                                  INTEGER,
        	ltmClientSslAllowNonssl                                   INTEGER,
        	ltmClientSslSessionTicket                                 INTEGER,
        	ltmClientSslFwdpEnabled                                   INTEGER,
        	ltmClientSslFwdpCaKey                                     LongDisplayString,
        	ltmClientSslFwdpCaCert                                    LongDisplayString,
        	ltmClientSslFwdpCaPassphrase                              LongDisplayString,
        	ltmClientSslFwdpCertLifespan                              Gauge,
        	ltmClientSslFwdpCertExtensionIncludes                     Gauge,
        	ltmClientSslFwdpLookupByIpaddrPort                        INTEGER,
        	ltmClientSslGenericAlert                                  INTEGER,
        	ltmClientSslSslSignHash                                   INTEGER,
        	ltmClientSslFwdpBypassEnabled                             INTEGER,
        	ltmClientSslFwdpBypassDipBList                            LongDisplayString,
        	ltmClientSslFwdpBypassDipWList                            LongDisplayString,
        	ltmClientSslFwdpBypassSipBList                            LongDisplayString,
        	ltmClientSslFwdpBypassSipWList                            LongDisplayString,
        	ltmClientSslFwdpBypassHnBList                             LongDisplayString,
        	ltmClientSslFwdpBypassHnWList                             LongDisplayString,
        	ltmClientSslProxySsl                                      INTEGER,
        	ltmClientSslProxySslPassthrough                           INTEGER,
        	ltmClientSslPeerNoRenegotiateTimeout                      Gauge,
        	ltmClientSslMaxRenegotiationsPerMin                       Gauge,
        	ltmClientSslSessionMirroring                              INTEGER,
        	ltmClientSslMaxAggregateRenegotiationsPerMin              Gauge,
        	ltmClientSslSessionTicketTimeout                          Gauge,
        	ltmClientSslAllowExpiredCrl                               INTEGER,
        	ltmClientSslMaxActiveHandshake                            Gauge,
        	ltmClientSslAllowDynamicRecordSizing                      INTEGER,
        	ltmClientSslMaximumRecordSize                             Gauge,
        	ltmClientSslBypassHsAlertEnabled                          INTEGER,
        	ltmClientSslBypassClientCertFailEnabled                   INTEGER,
        	ltmClientSslOcspStapling                                  INTEGER,
        	ltmClientSslNotifyCertStatusToVs                          INTEGER,
        	ltmClientSslC3dEnabled                                    INTEGER,
        	ltmClientSslCentityOcspObjName                            LongDisplayString,
        	ltmClientSslDropUnknownOcspStatus                         INTEGER,
        	ltmClientSslData0rttMode                                  INTEGER
	}

ltmClientSslName OBJECT-TYPE
	SYNTAX LongDisplayString
	MAX-ACCESS read-only
	STATUS current
	DESCRIPTION
		"The name of a client-side SSL profile."
	::= { ltmClientSslEntry 1 }

ltmClientSslConfigSource OBJECT-TYPE
	SYNTAX INTEGER {
		usercfg(0),
		basecfg(1)
	}
	MAX-ACCESS read-only
	STATUS current
	DESCRIPTION
		"The state that specifies whether this is a base/pre-configured profile
		or user defined profile."
	::= { ltmClientSslEntry 2 }

ltmClientSslDefaultName OBJECT-TYPE
	SYNTAX LongDisplayString
	MAX-ACCESS read-only
	STATUS current
	DESCRIPTION
		"The name of the profile from which the specified profile derives
		its attribute default values."
	::= { ltmClientSslEntry 3 }

ltmClientSslMode OBJECT-TYPE
	SYNTAX INTEGER {
		disabled(0),
		enabled(1)
	}
	MAX-ACCESS read-only
	STATUS current
	DESCRIPTION
		"The mode of this profile."
	::= { ltmClientSslEntry 4 }

ltmClientSslKey OBJECT-TYPE
	SYNTAX LongDisplayString
	MAX-ACCESS read-only
	STATUS	 deprecated
	DESCRIPTION
		"Deprecated! Please refer ltmClientSslCertKeyChain.
		The key file name."
	::= { ltmClientSslEntry 5 }

ltmClientSslCert OBJECT-TYPE
	SYNTAX LongDisplayString
	MAX-ACCESS read-only
	STATUS	 deprecated
	DESCRIPTION
		"Deprecated! Please refer ltmClientSslCertKeyChain.
		The certificate file name."
	::= { ltmClientSslEntry 6 }

ltmClientSslChain OBJECT-TYPE
	SYNTAX LongDisplayString
	MAX-ACCESS read-only
	STATUS	 deprecated
	DESCRIPTION
		"Deprecated! Please refer ltmClientSslCertKeyChain.
		The certificate chain file name."
	::= { ltmClientSslEntry 7 }

ltmClientSslCafile OBJECT-TYPE
	SYNTAX LongDisplayString
	MAX-ACCESS read-only
	STATUS current
	DESCRIPTION
		"The CA certificate file name."
	::= { ltmClientSslEntry 8 }

ltmClientSslCrlfile OBJECT-TYPE
	SYNTAX LongDisplayString
	MAX-ACCESS read-only
	STATUS current
	DESCRIPTION
		"The CRL file name."
	::= { ltmClientSslEntry 9 }

ltmClientSslClientcertca OBJECT-TYPE
	SYNTAX LongDisplayString
	MAX-ACCESS read-only
	STATUS current
	DESCRIPTION
		"The CA certificate file name."
	::= { ltmClientSslEntry 10 }

ltmClientSslCiphers OBJECT-TYPE
	SYNTAX LongDisplayString
	MAX-ACCESS read-only
	STATUS current
	DESCRIPTION
		"The set of ciphers available for client-side SSL negotiation."
	::= { ltmClientSslEntry 11 }

ltmClientSslPassphrase OBJECT-TYPE
	SYNTAX LongDisplayString
	MAX-ACCESS read-only
	STATUS	 deprecated
	DESCRIPTION
		"Deprecated! No longer supported.
		The key passphrase (if any)."
	::= { ltmClientSslEntry 12 }

ltmClientSslOptions OBJECT-TYPE
	SYNTAX Gauge
	MAX-ACCESS read-only
	STATUS current
	DESCRIPTION
		"The SSL options.
		SSLOPT_MICROSOFT_SESS_ID_BUG              = 1
		SSLOPT_NETSCAPE_CHALLENGE_BUG             = 2
		SSLOPT_NETSCAPE_REUSE_CIPHER_CHANGE_BUG   = 8
		SSLOPT_SSLREF2_REUSE_CERT_TYPE_BUG        = 16
		SSLOPT_MICROSOFT_BIG_SSLV3_BUFFER         = 32
		SSLOPT_MSIE_SSLV2_RSA_PADDING             = 64
		SSLOPT_SSLEAY_080_CLIENT_DH_BUG           = 128
		SSLOPT_TLS_D5_BUG                         = 256
		SSLOPT_TLS_BLOCK_PADDING_BUG              = 512
		SSLOPT_DONT_INSERT_EMPTY_FRAGMENTS        = 2048
		SSLOPT_ALL_BUGFIXES                       = 4095
		SSLOPT_PASSIVE_CLOSE                      = 4096
		SSLOPT_NO_SSL                             = 8192
		SSLOPT_NO_DTLS                            = 16384
		SSLOPT_NO_TLSv1_3                         = 32768
		SSLOPT_NO_SESSION_RESUMPTION_ON_RENEGOTIATION = 65536
		SSLOPT_NO_TLSv1_1                         = 131072
		SSLOPT_NO_TLSv1_2                         = 262144
		SSLOPT_NO_TLS                             = 524288
		SSLOPT_SINGLE_DH_USE                      = 1048576
		SSLOPT_EPHEMERAL_RSA                      = 2097152
		SSLOPT_CIPHER_SERVER_PREFERENCE           = 4194304
		SSLOPT_TLS_ROLLBACK_BUG                   = 8388608
		SSLOPT_NO_SSLv2                           = 16777216
		SSLOPT_NO_SSLv3                           = 33554432
		SSLOPT_NO_TLSv1                           = 67108864
		SSLOPT_PKCS1_CHECK_1                      = 134217728
		SSLOPT_PKCS1_CHECK_2                      = 268435456
		SSLOPT_NETSCAPE_CA_DN_BUG                 = 536870912
		SSLOPT_NETSCAPE_DEMO_CIPHER_CHANGE_BUG    = 1073741824"
	::= { ltmClientSslEntry 13 }

ltmClientSslModsslmethods OBJECT-TYPE
	SYNTAX INTEGER {
		false(0),
		true(1)
	}
	MAX-ACCESS read-only
	STATUS current
	DESCRIPTION
		"The ModSSL method emulation."
	::= { ltmClientSslEntry 14 }

ltmClientSslCacheSize OBJECT-TYPE
	SYNTAX Gauge
	MAX-ACCESS read-only
	STATUS current
	DESCRIPTION
		"The SSL session cache size."
	::= { ltmClientSslEntry 15 }

ltmClientSslCacheTimeout OBJECT-TYPE
	SYNTAX Gauge
	MAX-ACCESS read-only
	STATUS current
	DESCRIPTION
		"The SSL session cache timeout."
	::= { ltmClientSslEntry 16 }

ltmClientSslRenegotiatePeriod OBJECT-TYPE
	SYNTAX Gauge
	MAX-ACCESS read-only
	STATUS current
	DESCRIPTION
		"Time-based trigger."
	::= { ltmClientSslEntry 17 }

ltmClientSslRenegotiateSize OBJECT-TYPE
	SYNTAX Gauge
	MAX-ACCESS read-only
	STATUS current
	DESCRIPTION
		"Throughput-based trigger MB."
	::= { ltmClientSslEntry 18 }

ltmClientSslRenegotiateMaxRecordDelay OBJECT-TYPE
	SYNTAX Gauge
	MAX-ACCESS read-only
	STATUS current
	DESCRIPTION
		"The timeout of renegotiation."
	::= { ltmClientSslEntry 19 }

ltmClientSslHandshakeTimeout OBJECT-TYPE
	SYNTAX Gauge
	MAX-ACCESS read-only
	STATUS current
	DESCRIPTION
		"The handshake timeout in seconds."
	::= { ltmClientSslEntry 20 }

ltmClientSslAlertTimeout OBJECT-TYPE
	SYNTAX Gauge
	MAX-ACCESS read-only
	STATUS current
	DESCRIPTION
		"The alert timeout in seconds."
	::= { ltmClientSslEntry 21 }

ltmClientSslPeerCertMode OBJECT-TYPE
	SYNTAX INTEGER {
		ignore(0),
		require(1),
		request(2),
		auto(3)
	}
	MAX-ACCESS read-only
	STATUS current
	DESCRIPTION
		"The mode of peer certification."
	::= { ltmClientSslEntry 22 }

ltmClientSslAuthenticateOnce OBJECT-TYPE
	SYNTAX INTEGER {
		false(0),
		true(1)
	}
	MAX-ACCESS read-only
	STATUS current
	DESCRIPTION
		"The feature to request client cert once or with each SSL
		session renegotiation."
	::= { ltmClientSslEntry 23 }

ltmClientSslAuthenticateDepth OBJECT-TYPE
	SYNTAX Gauge
	MAX-ACCESS read-only
	STATUS current
	DESCRIPTION
		"The maximum traversal depth for client certificate chain."
	::= { ltmClientSslEntry 24 }

ltmClientSslUncleanShutdown OBJECT-TYPE
	SYNTAX INTEGER {
		false(0),
		true(1)
	}
	MAX-ACCESS read-only
	STATUS current
	DESCRIPTION
		"The state of shutdown for this SSL, whether it is unclean
		 shutdown (not sending a close notification alert when closing
		 connection.)."
	::= { ltmClientSslEntry 25 }

ltmClientSslStrictResume OBJECT-TYPE
	SYNTAX INTEGER {
		false(0),
		true(1)
	}
	MAX-ACCESS read-only
	STATUS current
	DESCRIPTION
		"Whether to enforce strict SSL session resumption
		 per RFC2246"
	::= { ltmClientSslEntry 26 }

ltmClientSslAllowNonssl OBJECT-TYPE
	SYNTAX INTEGER {
		false(0),
		true(1)
	}
	MAX-ACCESS read-only
	STATUS current
	DESCRIPTION
		"Whether to allow non-SSL connections to pass through as
		cleartext."
	::= { ltmClientSslEntry 27 }

ltmClientSslSessionTicket OBJECT-TYPE
	SYNTAX INTEGER {
		false(0),
		true(1)
	}
	MAX-ACCESS read-only
	STATUS current
	DESCRIPTION
		"Whether to enforce session ticket per RFC5077."
	::= { ltmClientSslEntry 28 }

ltmClientSslFwdpEnabled OBJECT-TYPE
	SYNTAX INTEGER {
		false(0),
		true(1)
	}
	MAX-ACCESS read-only
	STATUS current
	DESCRIPTION
		"Whether to enable SSL Forward Proxy."
	::= { ltmClientSslEntry 29 }

ltmClientSslFwdpCaKey OBJECT-TYPE
	SYNTAX LongDisplayString
	MAX-ACCESS read-only
	STATUS current
	DESCRIPTION
		"The CA key object name for Forward Proxy."
	::= { ltmClientSslEntry 30 }

ltmClientSslFwdpCaCert OBJECT-TYPE
	SYNTAX LongDisplayString
	MAX-ACCESS read-only
	STATUS current
	DESCRIPTION
		"The CA certificate object name for Forward Proxy."
	::= { ltmClientSslEntry 31 }

ltmClientSslFwdpCaPassphrase OBJECT-TYPE
	SYNTAX LongDisplayString
	MAX-ACCESS read-only
	STATUS	 deprecated
	DESCRIPTION
		"Deprecated! No longer supported.
	         The CA key passphrase for Forward Proxy (if any)."
	::= { ltmClientSslEntry 32 }

ltmClientSslFwdpCertLifespan OBJECT-TYPE
	SYNTAX Gauge
	MAX-ACCESS read-only
	STATUS current
	DESCRIPTION
		"The lifespan of the generated certificates for Forward Proxy."
	::= { ltmClientSslEntry 33 }

ltmClientSslFwdpCertExtensionIncludes OBJECT-TYPE
	SYNTAX Gauge
	MAX-ACCESS read-only
	STATUS current
	DESCRIPTION
		"The certificate extensions to include in generated certificates for
	        Forward Proxy.
	        SSL_FWDP_CERT_EXT_BASIC_CONSTRAINTS             = 2
	        SSL_FWDP_CERT_EXT_EXTENDED_KEY_USAGE            = 16
	        SSL_FWDP_CERT_EXT_KEY_USAGE                     = 128
	        SSL_FWDP_CERT_EXT_SUBJECT_ALTERNATIVE_NAME      = 256
	        SSL_FWDP_CERT_EXT_SUBJECT_DIRECTORY_ATTRIBUTES  = 512"
	::= { ltmClientSslEntry 34 }

ltmClientSslFwdpLookupByIpaddrPort OBJECT-TYPE
	SYNTAX INTEGER {
		false(0),
		true(1)
	}
	MAX-ACCESS read-only
	STATUS current
	DESCRIPTION
		"Whether to enable SSL Forward Proxy certificate caching by IPAddr-Port."
	::= { ltmClientSslEntry 35 }

ltmClientSslGenericAlert OBJECT-TYPE
	SYNTAX INTEGER {
		false(0),
		true(1)
	}
	MAX-ACCESS read-only
	STATUS current
	DESCRIPTION
		"Whether to use generic alert number in Alert message."
	::= { ltmClientSslEntry 36 }

ltmClientSslSslSignHash OBJECT-TYPE
	SYNTAX INTEGER {
		any(0),
		sha1(1),
		sha256(2),
		sha384(3)
	}
	MAX-ACCESS read-only
	STATUS current
	DESCRIPTION
		"The ssl sign hash algorithm."
	::= { ltmClientSslEntry 37 }

ltmClientSslFwdpBypassEnabled OBJECT-TYPE
	SYNTAX INTEGER {
		false(0),
		true(1)
	}
	MAX-ACCESS read-only
	STATUS current
	DESCRIPTION
		"Whether to enable SSL Forward Proxy Bypass."
	::= { ltmClientSslEntry 38 }

ltmClientSslFwdpBypassDipBList OBJECT-TYPE
	SYNTAX LongDisplayString
	MAX-ACCESS read-only
	STATUS current
	DESCRIPTION
		"The Forward Proxy Bypass Destination IP Blacklist (if any)."
	::= { ltmClientSslEntry 39 }

ltmClientSslFwdpBypassDipWList OBJECT-TYPE
	SYNTAX LongDisplayString
	MAX-ACCESS read-only
	STATUS current
	DESCRIPTION
		"The Forward Proxy Bypass Destination IP Whitelist (if any)."
	::= { ltmClientSslEntry 40 }

ltmClientSslFwdpBypassSipBList OBJECT-TYPE
	SYNTAX LongDisplayString
	MAX-ACCESS read-only
	STATUS current
	DESCRIPTION
		"The Forward Proxy Bypass Source IP Blacklist (if any)."
	::= { ltmClientSslEntry 41 }

ltmClientSslFwdpBypassSipWList OBJECT-TYPE
	SYNTAX LongDisplayString
	MAX-ACCESS read-only
	STATUS current
	DESCRIPTION
		"The Forward Proxy Bypass Source IP Whitelist (if any)."
	::= { ltmClientSslEntry 42 }

ltmClientSslFwdpBypassHnBList OBJECT-TYPE
	SYNTAX LongDisplayString
	MAX-ACCESS read-only
	STATUS current
	DESCRIPTION
		"The Forward Proxy Bypass Hostname Blacklist (if any)."
	::= { ltmClientSslEntry 43 }

ltmClientSslFwdpBypassHnWList OBJECT-TYPE
	SYNTAX LongDisplayString
	MAX-ACCESS read-only
	STATUS current
	DESCRIPTION
		"The Forward Proxy Bypass Hostname Whitelist (if any)."
	::= { ltmClientSslEntry 44 }

ltmClientSslProxySsl OBJECT-TYPE
	SYNTAX INTEGER {
		false(0),
		true(1)
	}
	MAX-ACCESS read-only
	STATUS current
	DESCRIPTION
		"Whether to enable Proxy SSL."
	::= { ltmClientSslEntry 45 }

ltmClientSslProxySslPassthrough OBJECT-TYPE
	SYNTAX INTEGER {
		false(0),
		true(1)
	}
	MAX-ACCESS read-only
	STATUS current
	DESCRIPTION
		"Whether to enable Proxy SSL passthrough."
	::= { ltmClientSslEntry 46 }

ltmClientSslPeerNoRenegotiateTimeout OBJECT-TYPE
	SYNTAX Gauge
	MAX-ACCESS read-only
	STATUS current
	DESCRIPTION
		"The peer no-renegotiate timeout in seconds."
	::= { ltmClientSslEntry 47 }

ltmClientSslMaxRenegotiationsPerMin OBJECT-TYPE
	SYNTAX Gauge
	MAX-ACCESS read-only
	STATUS current
	DESCRIPTION
		"Maximum SSL renegotiations per minute."
	::= { ltmClientSslEntry 48 }

ltmClientSslSessionMirroring OBJECT-TYPE
	SYNTAX INTEGER {
		false(0),
		true(1)
	}
	MAX-ACCESS read-only
	STATUS current
	DESCRIPTION
		"Whether to mirror ssl sessions to HA peer."
	::= { ltmClientSslEntry 49 }

ltmClientSslMaxAggregateRenegotiationsPerMin OBJECT-TYPE
	SYNTAX Gauge
	MAX-ACCESS read-only
	STATUS current
	DESCRIPTION
		"Maximum SSL aggregate renegotiations per minute."
	::= { ltmClientSslEntry 50 }

ltmClientSslSessionTicketTimeout OBJECT-TYPE
	SYNTAX Gauge
	MAX-ACCESS read-only
	STATUS current
	DESCRIPTION
		"The session ticket timeout."
	::= { ltmClientSslEntry 51 }

ltmClientSslAllowExpiredCrl OBJECT-TYPE
	SYNTAX INTEGER {
		false(0),
		true(1)
	}
	MAX-ACCESS read-only
	STATUS current
	DESCRIPTION
		"Whether to ignore a CRLs expiration."
	::= { ltmClientSslEntry 52 }

ltmClientSslMaxActiveHandshake OBJECT-TYPE
	SYNTAX Gauge
	MAX-ACCESS read-only
	STATUS current
	DESCRIPTION
		"Maximum number of allowed SSL active handshakes."
	::= { ltmClientSslEntry 53 }

ltmClientSslAllowDynamicRecordSizing OBJECT-TYPE
	SYNTAX INTEGER {
		false(0),
		true(1)
	}
	MAX-ACCESS read-only
	STATUS current
	DESCRIPTION
		"Allow dynamic record sizing."
	::= { ltmClientSslEntry 54 }

ltmClientSslMaximumRecordSize OBJECT-TYPE
	SYNTAX Gauge
	MAX-ACCESS read-only
	STATUS current
	DESCRIPTION
		"Maximum SSL application record size."
	::= { ltmClientSslEntry 55 }

ltmClientSslBypassHsAlertEnabled OBJECT-TYPE
	SYNTAX INTEGER {
		false(0),
		true(1)
	}
	MAX-ACCESS read-only
	STATUS current
	DESCRIPTION
		"Whether to enable forward-proxy bypass on handshake alert"
	::= { ltmClientSslEntry 56 }

ltmClientSslBypassClientCertFailEnabled OBJECT-TYPE
	SYNTAX INTEGER {
		false(0),
		true(1)
	}
	MAX-ACCESS read-only
	STATUS current
	DESCRIPTION
		"Whether to enable forward-proxy bypass on failed client cert"
	::= { ltmClientSslEntry 57 }

ltmClientSslOcspStapling OBJECT-TYPE
	SYNTAX INTEGER {
		false(0),
		true(1)
	}
	MAX-ACCESS read-only
	STATUS current
	DESCRIPTION
		"Whether to enable OCSP stapling."
	::= { ltmClientSslEntry 58 }

ltmClientSslNotifyCertStatusToVs OBJECT-TYPE
	SYNTAX INTEGER {
		false(0),
		true(1)
	}
	MAX-ACCESS read-only
	STATUS current
	DESCRIPTION
		"Whether to propagate certificate status to virtual server status."
	::= { ltmClientSslEntry 59 }

ltmClientSslC3dEnabled OBJECT-TYPE
	SYNTAX INTEGER {
		false(0),
		true(1)
	}
	MAX-ACCESS read-only
	STATUS current
	DESCRIPTION
		"Whether to enable SSL Client Certificate Constrained Delegation."
	::= { ltmClientSslEntry 60 }

ltmClientSslCentityOcspObjName OBJECT-TYPE
	SYNTAX LongDisplayString
	MAX-ACCESS read-only
	STATUS current
	DESCRIPTION
		"OCSP object name that the BIGIP SSL should use to connect
	         to the OCSP responder and check the client certificate status."
	::= { ltmClientSslEntry 61 }

ltmClientSslDropUnknownOcspStatus OBJECT-TYPE
	SYNTAX INTEGER {
		false(0),
		true(1)
	}
	MAX-ACCESS read-only
	STATUS current
	DESCRIPTION
		"BIGIP action when the OCSP returns unknown status.
	         The default value is drop, which causes the connection to be dropped.
	         Conversely, you can specify ignore to cuase the connection to ignore
	         the unknown status and continue."
	::= { ltmClientSslEntry 62 }

ltmClientSslData0rttMode OBJECT-TYPE
	SYNTAX INTEGER {
		disabled(0),
		enabledWithAntiReplay(1),
		enabledNoAntiReplay(2)
	}
	MAX-ACCESS read-only
	STATUS current
	DESCRIPTION
		"Specifies if TLSv1.3 should accept 0-RTT with early data, with or without
	         anti-replay. To protect against packet replay, F5 recommends that you
	         enable anti-replay. If disabled, TLSv1.3 will discard any early data."
	::= { ltmClientSslEntry 63 }

--==================================================================
-- Profile_clientssl_stat
--==================================================================
ltmClientSslStatResetStats OBJECT-TYPE
	SYNTAX INTEGER
	MAX-ACCESS read-write
	STATUS current
	DESCRIPTION
		"The action to reset resettable statistics data in ltmClientSslProfileStat.
		 Setting this value to 1 will reset statistics data.
		 Note, some statistics data may not be reset including data that are incremental counters."
	::= { ltmClientSslProfileStat 1 }

ltmClientSslStatNumber OBJECT-TYPE
	SYNTAX INTEGER
	MAX-ACCESS read-only
	STATUS current
	DESCRIPTION
		"The number of ltmClientSslProfileStat entries in the table."
	::= { ltmClientSslProfileStat 2 }

ltmClientSslStatTable OBJECT-TYPE
	SYNTAX SEQUENCE OF LtmClientSslStatEntry
	MAX-ACCESS not-accessible
	STATUS current
	DESCRIPTION
		"A table containing information of the client-side SSL profiles.(BIG-IP acts as an SSL server)"
	::= { ltmClientSslProfileStat 3 }

ltmClientSslStatEntry OBJECT-TYPE
	SYNTAX  LtmClientSslStatEntry
	MAX-ACCESS not-accessible
	STATUS current
	DESCRIPTION
		"Columns in the ltmClientSslStat Table"
	INDEX {
		ltmClientSslStatName
	}
	::= { ltmClientSslStatTable 1 }

LtmClientSslStatEntry ::=
	SEQUENCE {
        	ltmClientSslStatName                                      LongDisplayString,
        	ltmClientSslStatCurConns                                  Gauge,
        	ltmClientSslStatMaxConns                                  Counter64,
        	ltmClientSslStatCurNativeConns                            Gauge,
        	ltmClientSslStatMaxNativeConns                            Counter64,
        	ltmClientSslStatTotNativeConns                            Counter64,
        	ltmClientSslStatCurCompatConns                            Gauge,
        	ltmClientSslStatMaxCompatConns                            Counter64,
        	ltmClientSslStatTotCompatConns                            Counter64,
        	ltmClientSslStatEncryptedBytesIn                          Counter64,
        	ltmClientSslStatEncryptedBytesOut                         Counter64,
        	ltmClientSslStatDecryptedBytesIn                          Counter64,
        	ltmClientSslStatDecryptedBytesOut                         Counter64,
        	ltmClientSslStatRecordsIn                                 Counter64,
        	ltmClientSslStatRecordsOut                                Counter64,
        	ltmClientSslStatFullyHwAcceleratedConns                   Counter64,
        	ltmClientSslStatPartiallyHwAcceleratedConns               Counter64,
        	ltmClientSslStatNonHwAcceleratedConns                     Counter64,
        	ltmClientSslStatPrematureDisconnects                      Counter64,
        	ltmClientSslStatMidstreamRenegotiations                   Counter64,
        	ltmClientSslStatSessCacheCurEntries                       Gauge,
        	ltmClientSslStatSessCacheHits                             Counter64,
        	ltmClientSslStatSessCacheLookups                          Counter64,
        	ltmClientSslStatSessCacheOverflows                        Counter64,
        	ltmClientSslStatSessCacheInvalidations                    Counter64,
        	ltmClientSslStatPeercertValid                             Counter64,
        	ltmClientSslStatPeercertInvalid                           Counter64,
        	ltmClientSslStatPeercertNone                              Counter64,
        	ltmClientSslStatHandshakeFailures                         Counter64,
        	ltmClientSslStatBadRecords                                Counter64,
        	ltmClientSslStatFatalAlerts                               Counter64,
        	ltmClientSslStatSslv2                                     Counter64,
        	ltmClientSslStatSslv3                                     Counter64,
        	ltmClientSslStatTlsv1                                     Counter64,
        	ltmClientSslStatAdhKeyxchg                                Counter64,
        	ltmClientSslStatDhDssKeyxchg                              Counter64,
        	ltmClientSslStatDhRsaKeyxchg                              Counter64,
        	ltmClientSslStatDssKeyxchg                                Counter64,
        	ltmClientSslStatEdhDssKeyxchg                             Counter64,
        	ltmClientSslStatRsaKeyxchg                                Counter64,
        	ltmClientSslStatNullBulk                                  Counter64,
        	ltmClientSslStatAesBulk                                   Counter64,
        	ltmClientSslStatDesBulk                                   Counter64,
        	ltmClientSslStatIdeaBulk                                  Counter64,
        	ltmClientSslStatRc2Bulk                                   Counter64,
        	ltmClientSslStatRc4Bulk                                   Counter64,
        	ltmClientSslStatNullDigest                                Counter64,
        	ltmClientSslStatMd5Digest                                 Counter64,
        	ltmClientSslStatShaDigest                                 Counter64,
        	ltmClientSslStatNotssl                                    Counter64,
        	ltmClientSslStatEdhRsaKeyxchg                             Counter64,
        	ltmClientSslStatSecureHandshakes                          Counter64,
        	ltmClientSslStatInsecureHandshakeAccepts                  Counter64,
        	ltmClientSslStatInsecureHandshakeRejects                  Counter64,
        	ltmClientSslStatInsecureRenegotiationRejects              Counter64,
        	ltmClientSslStatSniRejects                                Counter64,
        	ltmClientSslStatTlsv11                                    Counter64,
        	ltmClientSslStatTlsv12                                    Counter64,
        	ltmClientSslStatDtlsv1                                    Counter64,
        	ltmClientSslStatReused                                    Counter64,
        	ltmClientSslStatReuseFailed                               Counter64,
        	ltmClientSslStatEcdheRsaKeyxchg                           Counter64,
        	ltmClientSslStatConns                                     Counter64,
        	ltmClientSslStatCachedCerts                               Counter64,
        	ltmClientSslStatEcdhRsaKeyxchg                            Counter64,
        	ltmClientSslStatEcdheEcdsaKeyxchg                         Counter64,
        	ltmClientSslStatEcdhEcdsaKeyxchg                          Counter64,
        	ltmClientSslStatDheDssKeyxchg                             Counter64,
        	ltmClientSslStatAesGcmBulk                                Counter64,
        	ltmClientSslStatDestinationIpBypasses                     Counter64,
        	ltmClientSslStatSourceIpBypasses                          Counter64,
        	ltmClientSslStatHostnameBypasses                          Counter64,
        	ltmClientSslStatRenegotiationsRejected                    Counter64,
        	ltmClientSslStatOcspStaplingConns                         Counter64,
        	ltmClientSslStatOcspStaplingResponseStatusErrors          Counter64,
        	ltmClientSslStatOcspStaplingResponseValidationErrors      Counter64,
        	ltmClientSslStatOcspStaplingCertStatusErrors              Counter64,
        	ltmClientSslStatOcspStaplingOcspConnHttpErrors            Counter64,
        	ltmClientSslStatOcspStaplingOcspConnTimeouts              Counter64,
        	ltmClientSslStatOcspStaplingOcspConnFailures              Counter64,
        	ltmClientSslStatAggregateRenegotiationsRejected           Counter64,
        	ltmClientSslStatSessionMirrorSuccess                      Counter64,
        	ltmClientSslStatSessionMirrorFailure                      Counter64,
        	ltmClientSslStatConnectionMirrorPeerReady                 Counter64,
        	ltmClientSslStatConnectionMirrorHaCtxSent                 Counter64,
        	ltmClientSslStatConnectionMirrorHaCtxRecv                 Counter64,
        	ltmClientSslStatConnectionMirrorHaHsSuccess               Counter64,
        	ltmClientSslStatConnectionMirrorHaFailure                 Counter64,
        	ltmClientSslStatConnectionMirrorHaTimeout                 Counter64,
        	ltmClientSslStatDtlsTxPushbacks                           Counter64,
        	ltmClientSslStatCamelliaBulk                              Counter64,
        	ltmClientSslStatActiveHandshakeRejected                   Counter64,
        	ltmClientSslStatCurrentActiveHandshakes                   Counter64,
        	ltmClientSslStatLicensedTps                               Counter64,
        	ltmClientSslStatRecordSize1k                              Counter64,
        	ltmClientSslStatRecordSize2k                              Counter64,
        	ltmClientSslStatRecordSize3k                              Counter64,
        	ltmClientSslStatRecordSize4k                              Counter64,
        	ltmClientSslStatRecordSize5k                              Counter64,
        	ltmClientSslStatRecordSize6k                              Counter64,
        	ltmClientSslStatRecordSize7k                              Counter64,
        	ltmClientSslStatRecordSize8k                              Counter64,
        	ltmClientSslStatRecordSize9k                              Counter64,
        	ltmClientSslStatRecordSize10k                             Counter64,
        	ltmClientSslStatRecordSize11k                             Counter64,
        	ltmClientSslStatRecordSize12k                             Counter64,
        	ltmClientSslStatRecordSize13k                             Counter64,
        	ltmClientSslStatRecordSize14k                             Counter64,
        	ltmClientSslStatRecordSize15k                             Counter64,
        	ltmClientSslStatRecordSize16k                             Counter64,
        	ltmClientSslStatExtendedMasterSecrets                     Counter64,
        	ltmClientSslStatBypassesHandshakeAlert                    Counter64,
        	ltmClientSslStatBypassClientCertificateRequest            Counter64,
        	ltmClientSslStatOcspFwdpClientsslCachedResp               Counter64,
        	ltmClientSslStatOcspFwdpClientsslCertStatusReq            Counter64,
        	ltmClientSslStatOcspFwdpClientsslStapledResp              Counter64,
        	ltmClientSslStatOcspFwdpClientsslRespstatusErrResp        Counter64,
        	ltmClientSslStatOcspFwdpClientsslInvalidCertResp          Counter64,
        	ltmClientSslStatOcspFwdpClientsslRevokedResp              Counter64,
        	ltmClientSslStatOcspFwdpClientsslUnknownResp              Counter64,
        	ltmClientSslStatC3dConns                                  Counter64,
        	ltmClientSslStatTlsv13                                    Counter64,
        	ltmClientSslStatChacha20Poly1305Bulk                      Counter64,
        	ltmClientSslStatData0rttAccepts                           Counter64,
        	ltmClientSslStatData0rttRejects                           Counter64,
        	ltmClientSslStatAesBulkOffload                            Counter64,
        	ltmClientSslStatAesGcmBulkOffload                         Counter64,
        	ltmClientSslStatChacha20Poly1305BulkOffld                 Counter64,
        	ltmClientSslStatDesBulkOffload                            Counter64,
        	ltmClientSslStatRc4BulkOffload                            Counter64,
        	ltmClientSslStatCamelliaBulkOffload                       Counter64,
        	ltmClientSslStatMd5DigestOffload                          Counter64,
        	ltmClientSslStatShaDigestOffload                          Counter64,
        	ltmClientSslStatSha224Digest                              Counter64,
        	ltmClientSslStatSha224DigestOffload                       Counter64,
        	ltmClientSslStatSha256Digest                              Counter64,
        	ltmClientSslStatSha256DigestOffload                       Counter64,
        	ltmClientSslStatSha384Digest                              Counter64,
        	ltmClientSslStatSha384DigestOffload                       Counter64,
        	ltmClientSslStatSha512Digest                              Counter64,
        	ltmClientSslStatSha512DigestOffload                       Counter64,
        	ltmClientSslStatDhGroupP256                               Counter64,
        	ltmClientSslStatDhGroupP256Offload                        Counter64,
        	ltmClientSslStatDhGroupP384                               Counter64,
        	ltmClientSslStatDhGroupP384Offload                        Counter64,
        	ltmClientSslStatDhGroupX25519                             Counter64,
        	ltmClientSslStatDhGroupX25519Offload                      Counter64,
        	ltmClientSslStatRsaKeySize1024                            Counter64,
        	ltmClientSslStatRsaKeySize1024Offload                     Counter64,
        	ltmClientSslStatRsaKeySize2048                            Counter64,
        	ltmClientSslStatRsaKeySize2048Offload                     Counter64,
        	ltmClientSslStatRsaKeySize4096                            Counter64,
        	ltmClientSslStatRsaKeySize4096Offload                     Counter64,
        	ltmClientSslStatTotalHandshakesSoftware                   Counter64,
        	ltmClientSslStatTotalHandshakesOffload                    Counter64
	}

ltmClientSslStatName OBJECT-TYPE
	SYNTAX LongDisplayString
	MAX-ACCESS read-only
	STATUS current
	DESCRIPTION
		"The name of a client-side SSL  profile."
	::= { ltmClientSslStatEntry 1 }

ltmClientSslStatCurConns OBJECT-TYPE
	SYNTAX Gauge
	MAX-ACCESS read-only
	STATUS current
	DESCRIPTION
		"The current number of concurrent connections with
		 established SSL sessions being maintained by the filter."
	::= { ltmClientSslStatEntry 2 }

ltmClientSslStatMaxConns OBJECT-TYPE
	SYNTAX Counter64
	MAX-ACCESS read-only
	STATUS current
	DESCRIPTION
		"The maximum number of concurrent connections with
		 established SSL sessions being maintained by the filter."
	::= { ltmClientSslStatEntry 3 }

ltmClientSslStatCurNativeConns OBJECT-TYPE
	SYNTAX Gauge
	MAX-ACCESS read-only
	STATUS current
	DESCRIPTION
		"The current number of concurrent native connections with
		 established SSL sessions being maintained by the filter."
	::= { ltmClientSslStatEntry 4 }

ltmClientSslStatMaxNativeConns OBJECT-TYPE
	SYNTAX Counter64
	MAX-ACCESS read-only
	STATUS current
	DESCRIPTION
		"The maximum number of concurrent native connections with
		 established SSL sessions being maintained by the filter."
	::= { ltmClientSslStatEntry 5 }

ltmClientSslStatTotNativeConns OBJECT-TYPE
	SYNTAX Counter64
	MAX-ACCESS read-only
	STATUS current
	DESCRIPTION
		"The total number of concurrent native connections with
		 established SSL sessions being maintained by the filter."
	::= { ltmClientSslStatEntry 6 }

ltmClientSslStatCurCompatConns OBJECT-TYPE
	SYNTAX Gauge
	MAX-ACCESS read-only
	STATUS current
	DESCRIPTION
		"The current number of concurrent compat connections with
		 established SSL sessions being maintained by the filter."
	::= { ltmClientSslStatEntry 7 }

ltmClientSslStatMaxCompatConns OBJECT-TYPE
	SYNTAX Counter64
	MAX-ACCESS read-only
	STATUS current
	DESCRIPTION
		"The maximum number of concurrent compat connections with
		 established SSL sessions being maintained by the filter."
	::= { ltmClientSslStatEntry 8 }

ltmClientSslStatTotCompatConns OBJECT-TYPE
	SYNTAX Counter64
	MAX-ACCESS read-only
	STATUS current
	DESCRIPTION
		"The total number of concurrent compat connections with
		 established SSL sessions being maintained by the filter."
	::= { ltmClientSslStatEntry 9 }

ltmClientSslStatEncryptedBytesIn OBJECT-TYPE
	SYNTAX Counter64
	MAX-ACCESS read-only
	STATUS current
	DESCRIPTION
		"The total encrypted bytes received."
	::= { ltmClientSslStatEntry 10 }

ltmClientSslStatEncryptedBytesOut OBJECT-TYPE
	SYNTAX Counter64
	MAX-ACCESS read-only
	STATUS current
	DESCRIPTION
		"The total encrypted bytes sent."
	::= { ltmClientSslStatEntry 11 }

ltmClientSslStatDecryptedBytesIn OBJECT-TYPE
	SYNTAX Counter64
	MAX-ACCESS read-only
	STATUS current
	DESCRIPTION
		"The total decrypted bytes received."
	::= { ltmClientSslStatEntry 12 }

ltmClientSslStatDecryptedBytesOut OBJECT-TYPE
	SYNTAX Counter64
	MAX-ACCESS read-only
	STATUS current
	DESCRIPTION
		"The total decrypted bytes sent."
	::= { ltmClientSslStatEntry 13 }

ltmClientSslStatRecordsIn OBJECT-TYPE
	SYNTAX Counter64
	MAX-ACCESS read-only
	STATUS current
	DESCRIPTION
		"The total records received."
	::= { ltmClientSslStatEntry 14 }

ltmClientSslStatRecordsOut OBJECT-TYPE
	SYNTAX Counter64
	MAX-ACCESS read-only
	STATUS current
	DESCRIPTION
		"The total records sent."
	::= { ltmClientSslStatEntry 15 }

ltmClientSslStatFullyHwAcceleratedConns OBJECT-TYPE
	SYNTAX Counter64
	MAX-ACCESS read-only
	STATUS current
	DESCRIPTION
		"Fully hardware-accelerated implies usage of the Cavium
		 Nitrox or similar hardware accelerator such that all
		 significant cryptographic operations are offloaded,
		 including but not limited to the SSL handshake (at least
		 the RSA/DSA/DH operations) and record processing (at least
		 the bulk cipher plus MAC)."
	::= { ltmClientSslStatEntry 16 }

ltmClientSslStatPartiallyHwAcceleratedConns OBJECT-TYPE
	SYNTAX Counter64
	MAX-ACCESS read-only
	STATUS current
	DESCRIPTION
		"Partially hardware-accelerated indicates that at least the
		 RSA decryptions are offloaded."
	::= { ltmClientSslStatEntry 17 }

ltmClientSslStatNonHwAcceleratedConns OBJECT-TYPE
	SYNTAX Counter64
	MAX-ACCESS read-only
	STATUS current
	DESCRIPTION
		"Non-accelerated connections are those for which no
		 steady-state hardware acceleration is available (either
		 because no hardware accelerators are available or because
		 the necessary cryptographic operations are unsupported).
		 Because the extent of hardware acceleration may not be known
		 until a connection has closed (mid-stream SSL handshakes
		 might renegotiate an SSL session not supported by hardware
		 acceleration), this statistic will not be updated for a
		 given connection until it has closed."
	::= { ltmClientSslStatEntry 18 }

ltmClientSslStatPrematureDisconnects OBJECT-TYPE
	SYNTAX Counter64
	MAX-ACCESS read-only
	STATUS current
	DESCRIPTION
		"The number of connections disconnected before SSL session
		 establishment: the total number of connections that were
		 prematurely closed before an SSL session was established,
		 not including connections in passthrough mode."
	::= { ltmClientSslStatEntry 19 }

ltmClientSslStatMidstreamRenegotiations OBJECT-TYPE
	SYNTAX Counter64
	MAX-ACCESS read-only
	STATUS current
	DESCRIPTION
		"The number of mid-stream SSL re-negotiations, not including
		 initial SSL session establishment."
	::= { ltmClientSslStatEntry 20 }

ltmClientSslStatSessCacheCurEntries OBJECT-TYPE
	SYNTAX Gauge
	MAX-ACCESS read-only
	STATUS current
	DESCRIPTION
		"The number of the current entries in this cache."
	::= { ltmClientSslStatEntry 21 }

ltmClientSslStatSessCacheHits OBJECT-TYPE
	SYNTAX Counter64
	MAX-ACCESS read-only
	STATUS current
	DESCRIPTION
		"The total number of the cache hits."
	::= { ltmClientSslStatEntry 22 }

ltmClientSslStatSessCacheLookups OBJECT-TYPE
	SYNTAX Counter64
	MAX-ACCESS read-only
	STATUS current
	DESCRIPTION
		"The total number of the cache lookups."
	::= { ltmClientSslStatEntry 23 }

ltmClientSslStatSessCacheOverflows OBJECT-TYPE
	SYNTAX Counter64
	MAX-ACCESS read-only
	STATUS current
	DESCRIPTION
		"The total number of the cache overflows."
	::= { ltmClientSslStatEntry 24 }

ltmClientSslStatSessCacheInvalidations OBJECT-TYPE
	SYNTAX Counter64
	MAX-ACCESS read-only
	STATUS current
	DESCRIPTION
		"The total number of the session invalidations."
	::= { ltmClientSslStatEntry 25 }

ltmClientSslStatPeercertValid OBJECT-TYPE
	SYNTAX Counter64
	MAX-ACCESS read-only
	STATUS current
	DESCRIPTION
		"The total number of the valid certificates."
	::= { ltmClientSslStatEntry 26 }

ltmClientSslStatPeercertInvalid OBJECT-TYPE
	SYNTAX Counter64
	MAX-ACCESS read-only
	STATUS current
	DESCRIPTION
		"The total number of the invalid certificates."
	::= { ltmClientSslStatEntry 27 }

ltmClientSslStatPeercertNone OBJECT-TYPE
	SYNTAX Counter64
	MAX-ACCESS read-only
	STATUS current
	DESCRIPTION
		"The total number of connections without certificates."
	::= { ltmClientSslStatEntry 28 }

ltmClientSslStatHandshakeFailures OBJECT-TYPE
	SYNTAX Counter64
	MAX-ACCESS read-only
	STATUS current
	DESCRIPTION
		"The total number of handshake failures."
	::= { ltmClientSslStatEntry 29 }

ltmClientSslStatBadRecords OBJECT-TYPE
	SYNTAX Counter64
	MAX-ACCESS read-only
	STATUS current
	DESCRIPTION
		"The total number of the bad records."
	::= { ltmClientSslStatEntry 30 }

ltmClientSslStatFatalAlerts OBJECT-TYPE
	SYNTAX Counter64
	MAX-ACCESS read-only
	STATUS current
	DESCRIPTION
		"The total number of the fatal alerts."
	::= { ltmClientSslStatEntry 31 }

ltmClientSslStatSslv2 OBJECT-TYPE
	SYNTAX Counter64
	MAX-ACCESS read-only
	STATUS current
	DESCRIPTION
		"The total connections for SSL protocol version 2."
	::= { ltmClientSslStatEntry 32 }

ltmClientSslStatSslv3 OBJECT-TYPE
	SYNTAX Counter64
	MAX-ACCESS read-only
	STATUS current
	DESCRIPTION
		"The total connections for SSL protocol version 3."
	::= { ltmClientSslStatEntry 33 }

ltmClientSslStatTlsv1 OBJECT-TYPE
	SYNTAX Counter64
	MAX-ACCESS read-only
	STATUS current
	DESCRIPTION
		"The total connections for SSL TLS protocol version 1."
	::= { ltmClientSslStatEntry 34 }

ltmClientSslStatAdhKeyxchg OBJECT-TYPE
	SYNTAX Counter64
	MAX-ACCESS read-only
	STATUS current
	DESCRIPTION
		"The anonymous Diffie-Hellman."
	::= { ltmClientSslStatEntry 35 }

ltmClientSslStatDhDssKeyxchg OBJECT-TYPE
	SYNTAX Counter64
	MAX-ACCESS read-only
	STATUS	 deprecated
	DESCRIPTION
		"Deprecated! DSS certificate is obsolete in BIGIP.
		The diffie-Hellman w/ DSS certificate."
	::= { ltmClientSslStatEntry 36 }

ltmClientSslStatDhRsaKeyxchg OBJECT-TYPE
	SYNTAX Counter64
	MAX-ACCESS read-only
	STATUS current
	DESCRIPTION
		"The diffie-Hellman w/ RSA certificate."
	::= { ltmClientSslStatEntry 37 }

ltmClientSslStatDssKeyxchg OBJECT-TYPE
	SYNTAX Counter64
	MAX-ACCESS read-only
	STATUS	 deprecated
	DESCRIPTION
		"Deprecated! DSS certificate is obsolete in BIGIP.
		The DSS certificate."
	::= { ltmClientSslStatEntry 38 }

ltmClientSslStatEdhDssKeyxchg OBJECT-TYPE
	SYNTAX Counter64
	MAX-ACCESS read-only
	STATUS	 deprecated
	DESCRIPTION
		"Deprecated! DSS certificate is obsolete in BIGIP.
		The ephemeral Diffie-Hellman w/ DSS cert."
	::= { ltmClientSslStatEntry 39 }

ltmClientSslStatRsaKeyxchg OBJECT-TYPE
	SYNTAX Counter64
	MAX-ACCESS read-only
	STATUS current
	DESCRIPTION
		"The RSA certificate."
	::= { ltmClientSslStatEntry 40 }

ltmClientSslStatNullBulk OBJECT-TYPE
	SYNTAX Counter64
	MAX-ACCESS read-only
	STATUS current
	DESCRIPTION
		"No encryption."
	::= { ltmClientSslStatEntry 41 }

ltmClientSslStatAesBulk OBJECT-TYPE
	SYNTAX Counter64
	MAX-ACCESS read-only
	STATUS current
	DESCRIPTION
		"Advanced Encryption Standard (CBC)."
	::= { ltmClientSslStatEntry 42 }

ltmClientSslStatDesBulk OBJECT-TYPE
	SYNTAX Counter64
	MAX-ACCESS read-only
	STATUS current
	DESCRIPTION
		"Digital Encryption Standard (CBC)."
	::= { ltmClientSslStatEntry 43 }

ltmClientSslStatIdeaBulk OBJECT-TYPE
	SYNTAX Counter64
	MAX-ACCESS read-only
	STATUS current
	DESCRIPTION
		"IDEA (old SSLv2 cipher)."
	::= { ltmClientSslStatEntry 44 }

ltmClientSslStatRc2Bulk OBJECT-TYPE
	SYNTAX Counter64
	MAX-ACCESS read-only
	STATUS current
	DESCRIPTION
		"Rivest Cipher 2 (CBC)."
	::= { ltmClientSslStatEntry 45 }

ltmClientSslStatRc4Bulk OBJECT-TYPE
	SYNTAX Counter64
	MAX-ACCESS read-only
	STATUS current
	DESCRIPTION
		"Rivest Cipher 4 (CBC)."
	::= { ltmClientSslStatEntry 46 }

ltmClientSslStatNullDigest OBJECT-TYPE
	SYNTAX Counter64
	MAX-ACCESS read-only
	STATUS current
	DESCRIPTION
		"No message authentication."
	::= { ltmClientSslStatEntry 47 }

ltmClientSslStatMd5Digest OBJECT-TYPE
	SYNTAX Counter64
	MAX-ACCESS read-only
	STATUS current
	DESCRIPTION
		"Message Digest 5."
	::= { ltmClientSslStatEntry 48 }

ltmClientSslStatShaDigest OBJECT-TYPE
	SYNTAX Counter64
	MAX-ACCESS read-only
	STATUS current
	DESCRIPTION
		"Secure Hash Algorithm."
	::= { ltmClientSslStatEntry 49 }

ltmClientSslStatNotssl OBJECT-TYPE
	SYNTAX Counter64
	MAX-ACCESS read-only
	STATUS current
	DESCRIPTION
		"The total number of the bad client greetings."
	::= { ltmClientSslStatEntry 50 }

ltmClientSslStatEdhRsaKeyxchg OBJECT-TYPE
	SYNTAX Counter64
	MAX-ACCESS read-only
	STATUS current
	DESCRIPTION
		"Ephemeral Diffie-Hellman w/ RSA cert."
	::= { ltmClientSslStatEntry 51 }

ltmClientSslStatSecureHandshakes OBJECT-TYPE
	SYNTAX Counter64
	MAX-ACCESS read-only
	STATUS current
	DESCRIPTION
		"The number of handshakes, including mid-stream re-negotiations,
	         performed with peers supporting SSL secure renegotiation."
	::= { ltmClientSslStatEntry 52 }

ltmClientSslStatInsecureHandshakeAccepts OBJECT-TYPE
	SYNTAX Counter64
	MAX-ACCESS read-only
	STATUS current
	DESCRIPTION
		"The number of handshakes, including mid-stream re-negotiations,
	         performed with peers not supporting SSL secure renegotiation."
	::= { ltmClientSslStatEntry 53 }

ltmClientSslStatInsecureHandshakeRejects OBJECT-TYPE
	SYNTAX Counter64
	MAX-ACCESS read-only
	STATUS current
	DESCRIPTION
		"The number of rejected initial handshakes with peers
	         not supporting SSL secure renegotiation."
	::= { ltmClientSslStatEntry 54 }

ltmClientSslStatInsecureRenegotiationRejects OBJECT-TYPE
	SYNTAX Counter64
	MAX-ACCESS read-only
	STATUS current
	DESCRIPTION
		"The number of rejected renegotiation attempts by peers
	         not supporting SSL secure renegotiation."
	::= { ltmClientSslStatEntry 55 }

ltmClientSslStatSniRejects OBJECT-TYPE
	SYNTAX Counter64
	MAX-ACCESS read-only
	STATUS current
	DESCRIPTION
		"The number of rejected handshake attempts by peers
	         not supporting SSL SNI extension or having mismatched
	         server names."
	::= { ltmClientSslStatEntry 56 }

ltmClientSslStatTlsv11 OBJECT-TYPE
	SYNTAX Counter64
	MAX-ACCESS read-only
	STATUS current
	DESCRIPTION
		"The total connections for SSL TLS protocol version 1.1."
	::= { ltmClientSslStatEntry 57 }

ltmClientSslStatTlsv12 OBJECT-TYPE
	SYNTAX Counter64
	MAX-ACCESS read-only
	STATUS current
	DESCRIPTION
		"The total connections for SSL TLS protocol version 1.2."
	::= { ltmClientSslStatEntry 58 }

ltmClientSslStatDtlsv1 OBJECT-TYPE
	SYNTAX Counter64
	MAX-ACCESS read-only
	STATUS current
	DESCRIPTION
		"The total connections for SSL DTLS protocol version 1.0."
	::= { ltmClientSslStatEntry 59 }

ltmClientSslStatReused OBJECT-TYPE
	SYNTAX Counter64
	MAX-ACCESS read-only
	STATUS current
	DESCRIPTION
		"The total reused session ticket sessions."
	::= { ltmClientSslStatEntry 60 }

ltmClientSslStatReuseFailed OBJECT-TYPE
	SYNTAX Counter64
	MAX-ACCESS read-only
	STATUS current
	DESCRIPTION
		"The total failed reused session ticket sessions."
	::= { ltmClientSslStatEntry 61 }

ltmClientSslStatEcdheRsaKeyxchg OBJECT-TYPE
	SYNTAX Counter64
	MAX-ACCESS read-only
	STATUS current
	DESCRIPTION
		"Ephemeral ECDH w/ RSA cert."
	::= { ltmClientSslStatEntry 62 }

ltmClientSslStatConns OBJECT-TYPE
	SYNTAX Counter64
	MAX-ACCESS read-only
	STATUS current
	DESCRIPTION
		"The total connections using SSL FWDP feature."
	::= { ltmClientSslStatEntry 63 }

ltmClientSslStatCachedCerts OBJECT-TYPE
	SYNTAX Counter64
	MAX-ACCESS read-only
	STATUS current
	DESCRIPTION
		"The total cached SSL FWDP certificates."
	::= { ltmClientSslStatEntry 64 }

ltmClientSslStatEcdhRsaKeyxchg OBJECT-TYPE
	SYNTAX Counter64
	MAX-ACCESS read-only
	STATUS current
	DESCRIPTION
		"Fixed ECDH with RSA signed cert."
	::= { ltmClientSslStatEntry 65 }

ltmClientSslStatEcdheEcdsaKeyxchg OBJECT-TYPE
	SYNTAX Counter64
	MAX-ACCESS read-only
	STATUS current
	DESCRIPTION
		"Ephemeral ECDH with ECDSA cert."
	::= { ltmClientSslStatEntry 66 }

ltmClientSslStatEcdhEcdsaKeyxchg OBJECT-TYPE
	SYNTAX Counter64
	MAX-ACCESS read-only
	STATUS current
	DESCRIPTION
		"Fixed ECDH with ECDSA cert."
	::= { ltmClientSslStatEntry 67 }

ltmClientSslStatDheDssKeyxchg OBJECT-TYPE
	SYNTAX Counter64
	MAX-ACCESS read-only
	STATUS current
	DESCRIPTION
		"Ephemeral DH with DSS cert."
	::= { ltmClientSslStatEntry 68 }

ltmClientSslStatAesGcmBulk OBJECT-TYPE
	SYNTAX Counter64
	MAX-ACCESS read-only
	STATUS current
	DESCRIPTION
		"Advanced Encryption Standard Galois Counter Mode (AES-GCM)."
	::= { ltmClientSslStatEntry 69 }

ltmClientSslStatDestinationIpBypasses OBJECT-TYPE
	SYNTAX Counter64
	MAX-ACCESS read-only
	STATUS current
	DESCRIPTION
		"The total destination IP bypasses using SSL FWDP bypass feature."
	::= { ltmClientSslStatEntry 70 }

ltmClientSslStatSourceIpBypasses OBJECT-TYPE
	SYNTAX Counter64
	MAX-ACCESS read-only
	STATUS current
	DESCRIPTION
		"The total source IP bypasses using SSL FWDP bypass feature."
	::= { ltmClientSslStatEntry 71 }

ltmClientSslStatHostnameBypasses OBJECT-TYPE
	SYNTAX Counter64
	MAX-ACCESS read-only
	STATUS current
	DESCRIPTION
		"The total hostname bypasses using SSL FWDP bypass feature."
	::= { ltmClientSslStatEntry 72 }

ltmClientSslStatRenegotiationsRejected OBJECT-TYPE
	SYNTAX Counter64
	MAX-ACCESS read-only
	STATUS current
	DESCRIPTION
		"The total number of renegotiations rejected."
	::= { ltmClientSslStatEntry 73 }

ltmClientSslStatOcspStaplingConns OBJECT-TYPE
	SYNTAX Counter64
	MAX-ACCESS read-only
	STATUS current
	DESCRIPTION
		"The total connections sending the status-request extension in the client hello."
	::= { ltmClientSslStatEntry 74 }

ltmClientSslStatOcspStaplingResponseStatusErrors OBJECT-TYPE
	SYNTAX Counter64
	MAX-ACCESS read-only
	STATUS current
	DESCRIPTION
		"The total OCSP response errors."
	::= { ltmClientSslStatEntry 75 }

ltmClientSslStatOcspStaplingResponseValidationErrors OBJECT-TYPE
	SYNTAX Counter64
	MAX-ACCESS read-only
	STATUS current
	DESCRIPTION
		"The total OCSP response validation errors."
	::= { ltmClientSslStatEntry 76 }

ltmClientSslStatOcspStaplingCertStatusErrors OBJECT-TYPE
	SYNTAX Counter64
	MAX-ACCESS read-only
	STATUS current
	DESCRIPTION
		"The total certificate status errors (revoked, unknown)."
	::= { ltmClientSslStatEntry 77 }

ltmClientSslStatOcspStaplingOcspConnHttpErrors OBJECT-TYPE
	SYNTAX Counter64
	MAX-ACCESS read-only
	STATUS current
	DESCRIPTION
		"The total HTTP errors on the connection made to fetch the OCSP response."
	::= { ltmClientSslStatEntry 78 }

ltmClientSslStatOcspStaplingOcspConnTimeouts OBJECT-TYPE
	SYNTAX Counter64
	MAX-ACCESS read-only
	STATUS current
	DESCRIPTION
		"The total timeouts on the connection made to fetch the OCSP response."
	::= { ltmClientSslStatEntry 79 }

ltmClientSslStatOcspStaplingOcspConnFailures OBJECT-TYPE
	SYNTAX Counter64
	MAX-ACCESS read-only
	STATUS current
	DESCRIPTION
		"The total connection failures when fetching OCSP response."
	::= { ltmClientSslStatEntry 80 }

ltmClientSslStatAggregateRenegotiationsRejected OBJECT-TYPE
	SYNTAX Counter64
	MAX-ACCESS read-only
	STATUS current
	DESCRIPTION
		"The total number of aggregate renegotiations rejected."
	::= { ltmClientSslStatEntry 81 }

ltmClientSslStatSessionMirrorSuccess OBJECT-TYPE
	SYNTAX Counter64
	MAX-ACCESS read-only
	STATUS current
	DESCRIPTION
		"The total SSL sessions mirrored successfully."
	::= { ltmClientSslStatEntry 82 }

ltmClientSslStatSessionMirrorFailure OBJECT-TYPE
	SYNTAX Counter64
	MAX-ACCESS read-only
	STATUS current
	DESCRIPTION
		"The total SSL session mirror failures."
	::= { ltmClientSslStatEntry 83 }

ltmClientSslStatConnectionMirrorPeerReady OBJECT-TYPE
	SYNTAX Counter64
	MAX-ACCESS read-only
	STATUS current
	DESCRIPTION
		"The total SSL HA peer ready messages."
	::= { ltmClientSslStatEntry 84 }

ltmClientSslStatConnectionMirrorHaCtxSent OBJECT-TYPE
	SYNTAX Counter64
	MAX-ACCESS read-only
	STATUS current
	DESCRIPTION
		"The total SSL HA context sent messages."
	::= { ltmClientSslStatEntry 85 }

ltmClientSslStatConnectionMirrorHaCtxRecv OBJECT-TYPE
	SYNTAX Counter64
	MAX-ACCESS read-only
	STATUS current
	DESCRIPTION
		"The total SSL HA context received messages."
	::= { ltmClientSslStatEntry 86 }

ltmClientSslStatConnectionMirrorHaHsSuccess OBJECT-TYPE
	SYNTAX Counter64
	MAX-ACCESS read-only
	STATUS current
	DESCRIPTION
		"The total SSL HA handshake succesful."
	::= { ltmClientSslStatEntry 87 }

ltmClientSslStatConnectionMirrorHaFailure OBJECT-TYPE
	SYNTAX Counter64
	MAX-ACCESS read-only
	STATUS current
	DESCRIPTION
		"The total SSL HA failures."
	::= { ltmClientSslStatEntry 88 }

ltmClientSslStatConnectionMirrorHaTimeout OBJECT-TYPE
	SYNTAX Counter64
	MAX-ACCESS read-only
	STATUS current
	DESCRIPTION
		"The total SSL HA timeouts."
	::= { ltmClientSslStatEntry 89 }

ltmClientSslStatDtlsTxPushbacks OBJECT-TYPE
	SYNTAX Counter64
	MAX-ACCESS read-only
	STATUS current
	DESCRIPTION
		"The total number of the Datagram Transport Layer Security transmitted packets which are pushed back."
	::= { ltmClientSslStatEntry 90 }

ltmClientSslStatCamelliaBulk OBJECT-TYPE
	SYNTAX Counter64
	MAX-ACCESS read-only
	STATUS current
	DESCRIPTION
		"Camellia Cipher (CBC)."
	::= { ltmClientSslStatEntry 91 }

ltmClientSslStatActiveHandshakeRejected OBJECT-TYPE
	SYNTAX Counter64
	MAX-ACCESS read-only
	STATUS current
	DESCRIPTION
		"The total number of active handshakes rejected."
	::= { ltmClientSslStatEntry 92 }

ltmClientSslStatCurrentActiveHandshakes OBJECT-TYPE
	SYNTAX Counter64
	MAX-ACCESS read-only
	STATUS current
	DESCRIPTION
		"The total number of current active handshakes."
	::= { ltmClientSslStatEntry 93 }

ltmClientSslStatLicensedTps OBJECT-TYPE
	SYNTAX Counter64
	MAX-ACCESS read-only
	STATUS current
	DESCRIPTION
		"The licensed transactions per second (TPS) value."
	::= { ltmClientSslStatEntry 94 }

ltmClientSslStatRecordSize1k OBJECT-TYPE
	SYNTAX Counter64
	MAX-ACCESS read-only
	STATUS current
	DESCRIPTION
		"The number of records sized 0 to 1K sent."
	::= { ltmClientSslStatEntry 95 }

ltmClientSslStatRecordSize2k OBJECT-TYPE
	SYNTAX Counter64
	MAX-ACCESS read-only
	STATUS current
	DESCRIPTION
		"The number of records sized 1K to 2K sent."
	::= { ltmClientSslStatEntry 96 }

ltmClientSslStatRecordSize3k OBJECT-TYPE
	SYNTAX Counter64
	MAX-ACCESS read-only
	STATUS current
	DESCRIPTION
		"The number of records sized 2K to 3K sent."
	::= { ltmClientSslStatEntry 97 }

ltmClientSslStatRecordSize4k OBJECT-TYPE
	SYNTAX Counter64
	MAX-ACCESS read-only
	STATUS current
	DESCRIPTION
		"The number of records sized 3K to 4K sent."
	::= { ltmClientSslStatEntry 98 }

ltmClientSslStatRecordSize5k OBJECT-TYPE
	SYNTAX Counter64
	MAX-ACCESS read-only
	STATUS current
	DESCRIPTION
		"The number of records sized 4K to 5K sent."
	::= { ltmClientSslStatEntry 99 }

ltmClientSslStatRecordSize6k OBJECT-TYPE
	SYNTAX Counter64
	MAX-ACCESS read-only
	STATUS current
	DESCRIPTION
		"The number of records sized 5K to 6K sent."
	::= { ltmClientSslStatEntry 100 }

ltmClientSslStatRecordSize7k OBJECT-TYPE
	SYNTAX Counter64
	MAX-ACCESS read-only
	STATUS current
	DESCRIPTION
		"The number of records sized 6K to 7K sent."
	::= { ltmClientSslStatEntry 101 }

ltmClientSslStatRecordSize8k OBJECT-TYPE
	SYNTAX Counter64
	MAX-ACCESS read-only
	STATUS current
	DESCRIPTION
		"The number of records sized 7K to 8K sent."
	::= { ltmClientSslStatEntry 102 }

ltmClientSslStatRecordSize9k OBJECT-TYPE
	SYNTAX Counter64
	MAX-ACCESS read-only
	STATUS current
	DESCRIPTION
		"The number of records sized 8K to 9K sent."
	::= { ltmClientSslStatEntry 103 }

ltmClientSslStatRecordSize10k OBJECT-TYPE
	SYNTAX Counter64
	MAX-ACCESS read-only
	STATUS current
	DESCRIPTION
		"The number of records sized 9K to 10K sent."
	::= { ltmClientSslStatEntry 104 }

ltmClientSslStatRecordSize11k OBJECT-TYPE
	SYNTAX Counter64
	MAX-ACCESS read-only
	STATUS current
	DESCRIPTION
		"The number of records sized 10K to 11K sent."
	::= { ltmClientSslStatEntry 105 }

ltmClientSslStatRecordSize12k OBJECT-TYPE
	SYNTAX Counter64
	MAX-ACCESS read-only
	STATUS current
	DESCRIPTION
		"The number of records sized 11K to 12K sent."
	::= { ltmClientSslStatEntry 106 }

ltmClientSslStatRecordSize13k OBJECT-TYPE
	SYNTAX Counter64
	MAX-ACCESS read-only
	STATUS current
	DESCRIPTION
		"The number of records sized 12K to 13K sent."
	::= { ltmClientSslStatEntry 107 }

ltmClientSslStatRecordSize14k OBJECT-TYPE
	SYNTAX Counter64
	MAX-ACCESS read-only
	STATUS current
	DESCRIPTION
		"The number of records sized 13K to 14K sent."
	::= { ltmClientSslStatEntry 108 }

ltmClientSslStatRecordSize15k OBJECT-TYPE
	SYNTAX Counter64
	MAX-ACCESS read-only
	STATUS current
	DESCRIPTION
		"The number of records sized 14K to 15K sent."
	::= { ltmClientSslStatEntry 109 }

ltmClientSslStatRecordSize16k OBJECT-TYPE
	SYNTAX Counter64
	MAX-ACCESS read-only
	STATUS current
	DESCRIPTION
		"The number of records sized 15K to 16K sent."
	::= { ltmClientSslStatEntry 110 }

ltmClientSslStatExtendedMasterSecrets OBJECT-TYPE
	SYNTAX Counter64
	MAX-ACCESS read-only
	STATUS current
	DESCRIPTION
		"The total number of extended master secret handshakes."
	::= { ltmClientSslStatEntry 111 }

ltmClientSslStatBypassesHandshakeAlert OBJECT-TYPE
	SYNTAX Counter64
	MAX-ACCESS read-only
	STATUS current
	DESCRIPTION
		"The total ssl bypasses by receiving handshake alert."
	::= { ltmClientSslStatEntry 112 }

ltmClientSslStatBypassClientCertificateRequest OBJECT-TYPE
	SYNTAX Counter64
	MAX-ACCESS read-only
	STATUS current
	DESCRIPTION
		"The total ssl bypasses by failed client certificate request."
	::= { ltmClientSslStatEntry 113 }

ltmClientSslStatOcspFwdpClientsslCachedResp OBJECT-TYPE
	SYNTAX Counter64
	MAX-ACCESS read-only
	STATUS current
	DESCRIPTION
		"The total SSL OCSP FWDP certificate status responses cached."
	::= { ltmClientSslStatEntry 114 }

ltmClientSslStatOcspFwdpClientsslCertStatusReq OBJECT-TYPE
	SYNTAX Counter64
	MAX-ACCESS read-only
	STATUS current
	DESCRIPTION
		"The number of connections that requested OCSP certificate status."
	::= { ltmClientSslStatEntry 115 }

ltmClientSslStatOcspFwdpClientsslStapledResp OBJECT-TYPE
	SYNTAX Counter64
	MAX-ACCESS read-only
	STATUS current
	DESCRIPTION
		"The number of connections for which OCSP certificate status was stapled."
	::= { ltmClientSslStatEntry 116 }

ltmClientSslStatOcspFwdpClientsslRespstatusErrResp OBJECT-TYPE
	SYNTAX Counter64
	MAX-ACCESS read-only
	STATUS current
	DESCRIPTION
		"The number of connections for which stapled response did not indicate success."
	::= { ltmClientSslStatEntry 117 }

ltmClientSslStatOcspFwdpClientsslInvalidCertResp OBJECT-TYPE
	SYNTAX Counter64
	MAX-ACCESS read-only
	STATUS current
	DESCRIPTION
		"The number of connections for which invalid certificate was returned to indicate revoked response."
	::= { ltmClientSslStatEntry 118 }

ltmClientSslStatOcspFwdpClientsslRevokedResp OBJECT-TYPE
	SYNTAX Counter64
	MAX-ACCESS read-only
	STATUS current
	DESCRIPTION
		"The number of connections for which stapled response indicated revoked certificate status."
	::= { ltmClientSslStatEntry 119 }

ltmClientSslStatOcspFwdpClientsslUnknownResp OBJECT-TYPE
	SYNTAX Counter64
	MAX-ACCESS read-only
	STATUS current
	DESCRIPTION
		"The number of connections for which stapled response indicated unknown certificate status."
	::= { ltmClientSslStatEntry 120 }

ltmClientSslStatC3dConns OBJECT-TYPE
	SYNTAX Counter64
	MAX-ACCESS read-only
	STATUS current
	DESCRIPTION
		"The total connections using SSL C3D feature."
	::= { ltmClientSslStatEntry 121 }

ltmClientSslStatTlsv13 OBJECT-TYPE
	SYNTAX Counter64
	MAX-ACCESS read-only
	STATUS current
	DESCRIPTION
		"The total connections for SSL TLS protocol version 1.3."
	::= { ltmClientSslStatEntry 122 }

ltmClientSslStatChacha20Poly1305Bulk OBJECT-TYPE
	SYNTAX Counter64
	MAX-ACCESS read-only
	STATUS current
	DESCRIPTION
		"ChaCha20-Poly1305."
	::= { ltmClientSslStatEntry 123 }

ltmClientSslStatData0rttAccepts OBJECT-TYPE
	SYNTAX Counter64
	MAX-ACCESS read-only
	STATUS current
	DESCRIPTION
		"The total number of TLSv1.3 0-RTT connections with early data accepted."
	::= { ltmClientSslStatEntry 124 }

ltmClientSslStatData0rttRejects OBJECT-TYPE
	SYNTAX Counter64
	MAX-ACCESS read-only
	STATUS current
	DESCRIPTION
		"The total number of TLSv1.3 0-RTT connections rejected."
	::= { ltmClientSslStatEntry 125 }

ltmClientSslStatAesBulkOffload OBJECT-TYPE
	SYNTAX Counter64
	MAX-ACCESS read-only
	STATUS current
	DESCRIPTION
		"Advanced Encryption Standard (CBC) offload."
	::= { ltmClientSslStatEntry 126 }

ltmClientSslStatAesGcmBulkOffload OBJECT-TYPE
	SYNTAX Counter64
	MAX-ACCESS read-only
	STATUS current
	DESCRIPTION
		"Advanced Encryption Standard Galois Counter Mode (AES-GCM) offload."
	::= { ltmClientSslStatEntry 127 }

ltmClientSslStatChacha20Poly1305BulkOffld OBJECT-TYPE
	SYNTAX Counter64
	MAX-ACCESS read-only
	STATUS current
	DESCRIPTION
		"ChaCha20-Poly1305 offload."
	::= { ltmClientSslStatEntry 128 }

ltmClientSslStatDesBulkOffload OBJECT-TYPE
	SYNTAX Counter64
	MAX-ACCESS read-only
	STATUS current
	DESCRIPTION
		"Digital Encryption Standard (CBC) offload."
	::= { ltmClientSslStatEntry 129 }

ltmClientSslStatRc4BulkOffload OBJECT-TYPE
	SYNTAX Counter64
	MAX-ACCESS read-only
	STATUS current
	DESCRIPTION
		"Rivest Cipher 4 (CBC) offload."
	::= { ltmClientSslStatEntry 130 }

ltmClientSslStatCamelliaBulkOffload OBJECT-TYPE
	SYNTAX Counter64
	MAX-ACCESS read-only
	STATUS current
	DESCRIPTION
		"Camellia Cipher (CBC) offload."
	::= { ltmClientSslStatEntry 131 }

ltmClientSslStatMd5DigestOffload OBJECT-TYPE
	SYNTAX Counter64
	MAX-ACCESS read-only
	STATUS current
	DESCRIPTION
		"Message Digest 5 offload."
	::= { ltmClientSslStatEntry 132 }

ltmClientSslStatShaDigestOffload OBJECT-TYPE
	SYNTAX Counter64
	MAX-ACCESS read-only
	STATUS current
	DESCRIPTION
		"Secure Hash Algorithm offload."
	::= { ltmClientSslStatEntry 133 }

ltmClientSslStatSha224Digest OBJECT-TYPE
	SYNTAX Counter64
	MAX-ACCESS read-only
	STATUS current
	DESCRIPTION
		"Secure Hash Algorithm 224."
	::= { ltmClientSslStatEntry 134 }

ltmClientSslStatSha224DigestOffload OBJECT-TYPE
	SYNTAX Counter64
	MAX-ACCESS read-only
	STATUS current
	DESCRIPTION
		"Secure Hash Algorithm 224 offload."
	::= { ltmClientSslStatEntry 135 }

ltmClientSslStatSha256Digest OBJECT-TYPE
	SYNTAX Counter64
	MAX-ACCESS read-only
	STATUS current
	DESCRIPTION
		"Secure Hash Algorithm 256."
	::= { ltmClientSslStatEntry 136 }

ltmClientSslStatSha256DigestOffload OBJECT-TYPE
	SYNTAX Counter64
	MAX-ACCESS read-only
	STATUS current
	DESCRIPTION
		"Secure Hash Algorithm 256 offload."
	::= { ltmClientSslStatEntry 137 }

ltmClientSslStatSha384Digest OBJECT-TYPE
	SYNTAX Counter64
	MAX-ACCESS read-only
	STATUS current
	DESCRIPTION
		"Secure Hash Algorithm 384."
	::= { ltmClientSslStatEntry 138 }

ltmClientSslStatSha384DigestOffload OBJECT-TYPE
	SYNTAX Counter64
	MAX-ACCESS read-only
	STATUS current
	DESCRIPTION
		"Secure Hash Algorithm 384 offload."
	::= { ltmClientSslStatEntry 139 }

ltmClientSslStatSha512Digest OBJECT-TYPE
	SYNTAX Counter64
	MAX-ACCESS read-only
	STATUS current
	DESCRIPTION
		"Secure Hash Algorithm 512."
	::= { ltmClientSslStatEntry 140 }

ltmClientSslStatSha512DigestOffload OBJECT-TYPE
	SYNTAX Counter64
	MAX-ACCESS read-only
	STATUS current
	DESCRIPTION
		"Secure Hash Algorithm 512 offload."
	::= { ltmClientSslStatEntry 141 }

ltmClientSslStatDhGroupP256 OBJECT-TYPE
	SYNTAX Counter64
	MAX-ACCESS read-only
	STATUS current
	DESCRIPTION
		"DH Group P256."
	::= { ltmClientSslStatEntry 142 }

ltmClientSslStatDhGroupP256Offload OBJECT-TYPE
	SYNTAX Counter64
	MAX-ACCESS read-only
	STATUS current
	DESCRIPTION
		"DH Group P256 offload."
	::= { ltmClientSslStatEntry 143 }

ltmClientSslStatDhGroupP384 OBJECT-TYPE
	SYNTAX Counter64
	MAX-ACCESS read-only
	STATUS current
	DESCRIPTION
		"DH Group P384."
	::= { ltmClientSslStatEntry 144 }

ltmClientSslStatDhGroupP384Offload OBJECT-TYPE
	SYNTAX Counter64
	MAX-ACCESS read-only
	STATUS current
	DESCRIPTION
		"DH Group P384 offload."
	::= { ltmClientSslStatEntry 145 }

ltmClientSslStatDhGroupX25519 OBJECT-TYPE
	SYNTAX Counter64
	MAX-ACCESS read-only
	STATUS current
	DESCRIPTION
		"DH Group X25519."
	::= { ltmClientSslStatEntry 146 }

ltmClientSslStatDhGroupX25519Offload OBJECT-TYPE
	SYNTAX Counter64
	MAX-ACCESS read-only
	STATUS current
	DESCRIPTION
		"DH Group X25519 offload."
	::= { ltmClientSslStatEntry 147 }

ltmClientSslStatRsaKeySize1024 OBJECT-TYPE
	SYNTAX Counter64
	MAX-ACCESS read-only
	STATUS current
	DESCRIPTION
		"RSA key size 1024."
	::= { ltmClientSslStatEntry 148 }

ltmClientSslStatRsaKeySize1024Offload OBJECT-TYPE
	SYNTAX Counter64
	MAX-ACCESS read-only
	STATUS current
	DESCRIPTION
		"RSA key size 1024 offload."
	::= { ltmClientSslStatEntry 149 }

ltmClientSslStatRsaKeySize2048 OBJECT-TYPE
	SYNTAX Counter64
	MAX-ACCESS read-only
	STATUS current
	DESCRIPTION
		"RSA key size 2048."
	::= { ltmClientSslStatEntry 150 }

ltmClientSslStatRsaKeySize2048Offload OBJECT-TYPE
	SYNTAX Counter64
	MAX-ACCESS read-only
	STATUS current
	DESCRIPTION
		"RSA key size 2048_offload."
	::= { ltmClientSslStatEntry 151 }

ltmClientSslStatRsaKeySize4096 OBJECT-TYPE
	SYNTAX Counter64
	MAX-ACCESS read-only
	STATUS current
	DESCRIPTION
		"RSA key size 4096."
	::= { ltmClientSslStatEntry 152 }

ltmClientSslStatRsaKeySize4096Offload OBJECT-TYPE
	SYNTAX Counter64
	MAX-ACCESS read-only
	STATUS current
	DESCRIPTION
		"RSA key size 4096 offload."
	::= { ltmClientSslStatEntry 153 }

ltmClientSslStatTotalHandshakesSoftware OBJECT-TYPE
	SYNTAX Counter64
	MAX-ACCESS read-only
	STATUS current
	DESCRIPTION
		"Handshake records processed in software."
	::= { ltmClientSslStatEntry 154 }

ltmClientSslStatTotalHandshakesOffload OBJECT-TYPE
	SYNTAX Counter64
	MAX-ACCESS read-only
	STATUS current
	DESCRIPTION
		"Handshake records offloaded."
	::= { ltmClientSslStatEntry 155 }

--==================================================================
-- Profile_serverssl
--==================================================================
ltmServerSslNumber OBJECT-TYPE
	SYNTAX INTEGER
	MAX-ACCESS read-only
	STATUS current
	DESCRIPTION
		"The number of ltmServerSslProfile entries in the table."
	::= { ltmServerSslProfile 1 }

ltmServerSslTable OBJECT-TYPE
	SYNTAX SEQUENCE OF LtmServerSslEntry
	MAX-ACCESS not-accessible
	STATUS current
	DESCRIPTION
		"A table containing statistic information of the server-side SSL profiles.(BIG-IP acts as an SSL client)"
	::= { ltmServerSslProfile 2 }

ltmServerSslEntry OBJECT-TYPE
	SYNTAX  LtmServerSslEntry
	MAX-ACCESS not-accessible
	STATUS current
	DESCRIPTION
		"Columns in the ltmServerSsl Table"
	INDEX {
		ltmServerSslName
	}
	::= { ltmServerSslTable 1 }

LtmServerSslEntry ::=
	SEQUENCE {
        	ltmServerSslName                                          LongDisplayString,
        	ltmServerSslConfigSource                                  INTEGER,
        	ltmServerSslDefaultName                                   LongDisplayString,
        	ltmServerSslMode                                          INTEGER,
        	ltmServerSslKey                                           LongDisplayString,
        	ltmServerSslCert                                          LongDisplayString,
        	ltmServerSslChain                                         LongDisplayString,
        	ltmServerSslCafile                                        LongDisplayString,
        	ltmServerSslCrlfile                                       LongDisplayString,
        	ltmServerSslCiphers                                       LongDisplayString,
        	ltmServerSslPassphrase                                    LongDisplayString,
        	ltmServerSslOptions                                       Gauge,
        	ltmServerSslModsslmethods                                 INTEGER,
        	ltmServerSslRenegotiatePeriod                             Gauge,
        	ltmServerSslRenegotiateSize                               Gauge,
        	ltmServerSslPeerCertMode                                  INTEGER,
        	ltmServerSslAuthenticateOnce                              INTEGER,
        	ltmServerSslAuthenticateDepth                             Gauge,
        	ltmServerSslAuthenticateName                              LongDisplayString,
        	ltmServerSslUncleanShutdown                               INTEGER,
        	ltmServerSslStrictResume                                  INTEGER,
        	ltmServerSslHandshakeTimeout                              Gauge,
        	ltmServerSslAlertTimeout                                  Gauge,
        	ltmServerSslCacheSize                                     Gauge,
        	ltmServerSslCacheTimeout                                  Gauge,
        	ltmServerSslSessionTicket                                 INTEGER,
        	ltmServerSslFwdpEnabled                                   INTEGER,
        	ltmServerSslDropExpCert                                   INTEGER,
        	ltmServerSslDropUntrustCa                                 INTEGER,
        	ltmServerSslGenericAlert                                  INTEGER,
        	ltmServerSslSslSignHash                                   INTEGER,
        	ltmServerSslFwdpBypassEnabled                             INTEGER,
        	ltmServerSslProxySsl                                      INTEGER,
        	ltmServerSslProxySslPassthrough                           INTEGER,
        	ltmServerSslSessionMirroring                              INTEGER,
        	ltmServerSslAllowExpiredCrl                               INTEGER,
        	ltmServerSslMaxActiveHandshake                            Gauge,
        	ltmServerSslBypassHsAlertEnabled                          INTEGER,
        	ltmServerSslBypassClientCertFailEnabled                   INTEGER,
        	ltmServerSslCentityOcspObjName                            LongDisplayString,
        	ltmServerSslC3dEnabled                                    INTEGER,
        	ltmServerSslC3dCaKey                                      LongDisplayString,
        	ltmServerSslC3dCaCert                                     LongDisplayString,
        	ltmServerSslC3dCaPassphrase                               LongDisplayString,
        	ltmServerSslC3dCertLifespan                               Gauge,
        	ltmServerSslC3dCertExtensionIncludes                      Gauge,
        	ltmServerSslData0rttMode                                  INTEGER
	}

ltmServerSslName OBJECT-TYPE
	SYNTAX LongDisplayString
	MAX-ACCESS read-only
	STATUS current
	DESCRIPTION
		"The name of a server-side SSL  profile."
	::= { ltmServerSslEntry 1 }

ltmServerSslConfigSource OBJECT-TYPE
	SYNTAX INTEGER {
		usercfg(0),
		basecfg(1)
	}
	MAX-ACCESS read-only
	STATUS current
	DESCRIPTION
		"The state that specifies whether this is a base/pre-configured profile
		or user defined profile."
	::= { ltmServerSslEntry 2 }

ltmServerSslDefaultName OBJECT-TYPE
	SYNTAX LongDisplayString
	MAX-ACCESS read-only
	STATUS current
	DESCRIPTION
		"The name of the profile from which the specified profile derives
		its attribute default values."
	::= { ltmServerSslEntry 3 }

ltmServerSslMode OBJECT-TYPE
	SYNTAX INTEGER {
		disabled(0),
		enabled(1)
	}
	MAX-ACCESS read-only
	STATUS current
	DESCRIPTION
		"The status of this profile."
	::= { ltmServerSslEntry 4 }

ltmServerSslKey OBJECT-TYPE
	SYNTAX LongDisplayString
	MAX-ACCESS read-only
	STATUS current
	DESCRIPTION
		"The key file name."
	::= { ltmServerSslEntry 5 }

ltmServerSslCert OBJECT-TYPE
	SYNTAX LongDisplayString
	MAX-ACCESS read-only
	STATUS current
	DESCRIPTION
		"The certificate file name."
	::= { ltmServerSslEntry 6 }

ltmServerSslChain OBJECT-TYPE
	SYNTAX LongDisplayString
	MAX-ACCESS read-only
	STATUS current
	DESCRIPTION
		"The certificate chain file name."
	::= { ltmServerSslEntry 7 }

ltmServerSslCafile OBJECT-TYPE
	SYNTAX LongDisplayString
	MAX-ACCESS read-only
	STATUS current
	DESCRIPTION
		"The CA certificate file name."
	::= { ltmServerSslEntry 8 }

ltmServerSslCrlfile OBJECT-TYPE
	SYNTAX LongDisplayString
	MAX-ACCESS read-only
	STATUS current
	DESCRIPTION
		"The CRL file name."
	::= { ltmServerSslEntry 9 }

ltmServerSslCiphers OBJECT-TYPE
	SYNTAX LongDisplayString
	MAX-ACCESS read-only
	STATUS current
	DESCRIPTION
		"The set of ciphers available for server-side SSL negotiation."
	::= { ltmServerSslEntry 10 }

ltmServerSslPassphrase OBJECT-TYPE
	SYNTAX LongDisplayString
	MAX-ACCESS read-only
	STATUS	 deprecated
	DESCRIPTION
		"Deprecated! No longer supported.
	        The key passphrase (if any)."
	::= { ltmServerSslEntry 11 }

ltmServerSslOptions OBJECT-TYPE
	SYNTAX Gauge
	MAX-ACCESS read-only
	STATUS current
	DESCRIPTION
		"The SSL options.
		SSLOPT_MICROSOFT_SESS_ID_BUG              = 1
		SSLOPT_NETSCAPE_CHALLENGE_BUG             = 2
		SSLOPT_NETSCAPE_REUSE_CIPHER_CHANGE_BUG   = 8
		SSLOPT_SSLREF2_REUSE_CERT_TYPE_BUG        = 16
		SSLOPT_MICROSOFT_BIG_SSLV3_BUFFER         = 32
		SSLOPT_MSIE_SSLV2_RSA_PADDING             = 64
		SSLOPT_SSLEAY_080_CLIENT_DH_BUG           = 128
		SSLOPT_TLS_D5_BUG                         = 256
		SSLOPT_TLS_BLOCK_PADDING_BUG              = 512
		SSLOPT_DONT_INSERT_EMPTY_FRAGMENTS        = 2048
		SSLOPT_ALL_BUGFIXES                       = 4095
		SSLOPT_PASSIVE_CLOSE                      = 4096
		SSLOPT_NO_SSL                             = 8192
		SSLOPT_NO_DTLS                            = 16384
		SSLOPT_NO_TLSv1_3                         = 32768
		SSLOPT_NO_SESSION_RESUMPTION_ON_RENEGOTIATION = 65536
		SSLOPT_NO_TLSv1_1                         = 131072
		SSLOPT_NO_TLSv1_2                         = 262144
		SSLOPT_NO_TLS                             = 524288
		SSLOPT_SINGLE_DH_USE                      = 1048576
		SSLOPT_EPHEMERAL_RSA                      = 2097152
		SSLOPT_CIPHER_SERVER_PREFERENCE           = 4194304
		SSLOPT_TLS_ROLLBACK_BUG                   = 8388608
		SSLOPT_NO_SSLv2                           = 16777216
		SSLOPT_NO_SSLv3                           = 33554432
		SSLOPT_NO_TLSv1                           = 67108864
		SSLOPT_PKCS1_CHECK_1                      = 134217728
		SSLOPT_PKCS1_CHECK_2                      = 268435456
		SSLOPT_NETSCAPE_CA_DN_BUG                 = 536870912
		SSLOPT_NETSCAPE_DEMO_CIPHER_CHANGE_BUG    = 1073741824"
	::= { ltmServerSslEntry 12 }

ltmServerSslModsslmethods OBJECT-TYPE
	SYNTAX INTEGER {
		false(0),
		true(1)
	}
	MAX-ACCESS read-only
	STATUS current
	DESCRIPTION
		"The status of using ModSSL method emulation."
	::= { ltmServerSslEntry 13 }

ltmServerSslRenegotiatePeriod OBJECT-TYPE
	SYNTAX Gauge
	MAX-ACCESS read-only
	STATUS current
	DESCRIPTION
		"Time-based trigger."
	::= { ltmServerSslEntry 14 }

ltmServerSslRenegotiateSize OBJECT-TYPE
	SYNTAX Gauge
	MAX-ACCESS read-only
	STATUS current
	DESCRIPTION
		"Throughput-based trigger MB."
	::= { ltmServerSslEntry 15 }

ltmServerSslPeerCertMode OBJECT-TYPE
	SYNTAX INTEGER {
		ignore(0),
		require(1)
	}
	MAX-ACCESS read-only
	STATUS current
	DESCRIPTION
		"The mode of peer certification."
	::= { ltmServerSslEntry 16 }

ltmServerSslAuthenticateOnce OBJECT-TYPE
	SYNTAX INTEGER {
		false(0),
		true(1)
	}
	MAX-ACCESS read-only
	STATUS current
	DESCRIPTION
		"The feature to request server cert with each SSL session
		renegotiation."
	::= { ltmServerSslEntry 17 }

ltmServerSslAuthenticateDepth OBJECT-TYPE
	SYNTAX Gauge
	MAX-ACCESS read-only
	STATUS current
	DESCRIPTION
		"The max traversal depth for client certificate chain."
	::= { ltmServerSslEntry 18 }

ltmServerSslAuthenticateName OBJECT-TYPE
	SYNTAX LongDisplayString
	MAX-ACCESS read-only
	STATUS current
	DESCRIPTION
		"The expected server certificate DN(Domain Name)."
	::= { ltmServerSslEntry 19 }

ltmServerSslUncleanShutdown OBJECT-TYPE
	SYNTAX INTEGER {
		false(0),
		true(1)
	}
	MAX-ACCESS read-only
	STATUS current
	DESCRIPTION
		"The state of shutdown for this SSL, whether it is unclean
		 shutdown (not sending a close notification alert when closing
		 connection.)."
	::= { ltmServerSslEntry 20 }

ltmServerSslStrictResume OBJECT-TYPE
	SYNTAX INTEGER {
		false(0),
		true(1)
	}
	MAX-ACCESS read-only
	STATUS current
	DESCRIPTION
		"The feature whether to enforce strict SSL session resumption
		 per RFC2246"
	::= { ltmServerSslEntry 21 }

ltmServerSslHandshakeTimeout OBJECT-TYPE
	SYNTAX Gauge
	MAX-ACCESS read-only
	STATUS current
	DESCRIPTION
		"The handshake timeout in seconds."
	::= { ltmServerSslEntry 22 }

ltmServerSslAlertTimeout OBJECT-TYPE
	SYNTAX Gauge
	MAX-ACCESS read-only
	STATUS current
	DESCRIPTION
		"The alert timeout in seconds."
	::= { ltmServerSslEntry 23 }

ltmServerSslCacheSize OBJECT-TYPE
	SYNTAX Gauge
	MAX-ACCESS read-only
	STATUS current
	DESCRIPTION
		"The SSL session cache size."
	::= { ltmServerSslEntry 24 }

ltmServerSslCacheTimeout OBJECT-TYPE
	SYNTAX Gauge
	MAX-ACCESS read-only
	STATUS current
	DESCRIPTION
		"The SSL session cache timeout."
	::= { ltmServerSslEntry 25 }

ltmServerSslSessionTicket OBJECT-TYPE
	SYNTAX INTEGER {
		false(0),
		true(1)
	}
	MAX-ACCESS read-only
	STATUS current
	DESCRIPTION
		"Whether to enforce session ticket per RFC5077."
	::= { ltmServerSslEntry 26 }

ltmServerSslFwdpEnabled OBJECT-TYPE
	SYNTAX INTEGER {
		false(0),
		true(1)
	}
	MAX-ACCESS read-only
	STATUS current
	DESCRIPTION
		"Whether to enable SSL Forward Proxy."
	::= { ltmServerSslEntry 27 }

ltmServerSslDropExpCert OBJECT-TYPE
	SYNTAX INTEGER {
		ignore(0),
		drop(1),
		mask(2)
	}
	MAX-ACCESS read-only
	STATUS current
	DESCRIPTION
		"Whether to drop or ignore or mask connection when server certificate is expired."
	::= { ltmServerSslEntry 28 }

ltmServerSslDropUntrustCa OBJECT-TYPE
	SYNTAX INTEGER {
		ignore(0),
		drop(1),
		mask(2)
	}
	MAX-ACCESS read-only
	STATUS current
	DESCRIPTION
		"Whether to drop or ignore or mask connection when server certificate has invalid CA."
	::= { ltmServerSslEntry 29 }

ltmServerSslGenericAlert OBJECT-TYPE
	SYNTAX INTEGER {
		false(0),
		true(1)
	}
	MAX-ACCESS read-only
	STATUS current
	DESCRIPTION
		"Whether to use generic alert number in Alert message."
	::= { ltmServerSslEntry 30 }

ltmServerSslSslSignHash OBJECT-TYPE
	SYNTAX INTEGER {
		any(0),
		sha1(1),
		sha256(2),
		sha384(3)
	}
	MAX-ACCESS read-only
	STATUS current
	DESCRIPTION
		"The ssl sign hash algorithm."
	::= { ltmServerSslEntry 31 }

ltmServerSslFwdpBypassEnabled OBJECT-TYPE
	SYNTAX INTEGER {
		false(0),
		true(1)
	}
	MAX-ACCESS read-only
	STATUS current
	DESCRIPTION
		"Whether to enable SSL Forward Proxy Bypass."
	::= { ltmServerSslEntry 32 }

ltmServerSslProxySsl OBJECT-TYPE
	SYNTAX INTEGER {
		false(0),
		true(1)
	}
	MAX-ACCESS read-only
	STATUS current
	DESCRIPTION
		"Whether to enable Proxy SSL."
	::= { ltmServerSslEntry 33 }

ltmServerSslProxySslPassthrough OBJECT-TYPE
	SYNTAX INTEGER {
		false(0),
		true(1)
	}
	MAX-ACCESS read-only
	STATUS current
	DESCRIPTION
		"Whether to enable Proxy SSL passthrough."
	::= { ltmServerSslEntry 34 }

ltmServerSslSessionMirroring OBJECT-TYPE
	SYNTAX INTEGER {
		false(0),
		true(1)
	}
	MAX-ACCESS read-only
	STATUS current
	DESCRIPTION
		"Whether to mirror ssl sessions to HA peer."
	::= { ltmServerSslEntry 35 }

ltmServerSslAllowExpiredCrl OBJECT-TYPE
	SYNTAX INTEGER {
		false(0),
		true(1)
	}
	MAX-ACCESS read-only
	STATUS current
	DESCRIPTION
		"Whether to ignore a CRLs expiration."
	::= { ltmServerSslEntry 36 }

ltmServerSslMaxActiveHandshake OBJECT-TYPE
	SYNTAX Gauge
	MAX-ACCESS read-only
	STATUS current
	DESCRIPTION
		"Maximum number of allowed SSL active handshakes."
	::= { ltmServerSslEntry 37 }

ltmServerSslBypassHsAlertEnabled OBJECT-TYPE
	SYNTAX INTEGER {
		false(0),
		true(1)
	}
	MAX-ACCESS read-only
	STATUS current
	DESCRIPTION
		"Whether to enable forward-proxy bypass on handshake alert"
	::= { ltmServerSslEntry 38 }

ltmServerSslBypassClientCertFailEnabled OBJECT-TYPE
	SYNTAX INTEGER {
		false(0),
		true(1)
	}
	MAX-ACCESS read-only
	STATUS current
	DESCRIPTION
		"Whether to enable forward-proxy bypass on failed client cert"
	::= { ltmServerSslEntry 39 }

ltmServerSslCentityOcspObjName OBJECT-TYPE
	SYNTAX LongDisplayString
	MAX-ACCESS read-only
	STATUS current
	DESCRIPTION
		"The name of OCSP profile used to enable OCSP stapling and validation of server certificate status."
	::= { ltmServerSslEntry 40 }

ltmServerSslC3dEnabled OBJECT-TYPE
	SYNTAX INTEGER {
		false(0),
		true(1)
	}
	MAX-ACCESS read-only
	STATUS current
	DESCRIPTION
		"Whether to enable SSL Client Certificate Constrained Delegation."
	::= { ltmServerSslEntry 41 }

ltmServerSslC3dCaKey OBJECT-TYPE
	SYNTAX LongDisplayString
	MAX-ACCESS read-only
	STATUS current
	DESCRIPTION
		"The CA key object name for Client Certificate Constrained Delegation."
	::= { ltmServerSslEntry 42 }

ltmServerSslC3dCaCert OBJECT-TYPE
	SYNTAX LongDisplayString
	MAX-ACCESS read-only
	STATUS current
	DESCRIPTION
		"The CA certificate object name for Client Certificate Constrained Delegation."
	::= { ltmServerSslEntry 43 }

ltmServerSslC3dCaPassphrase OBJECT-TYPE
	SYNTAX LongDisplayString
	MAX-ACCESS read-only
	STATUS	 deprecated
	DESCRIPTION
		"Deprecated! No longer supported.
	        The CA key passphrase for Client Certificate Constrained Delegation (if any)."
	::= { ltmServerSslEntry 44 }

ltmServerSslC3dCertLifespan OBJECT-TYPE
	SYNTAX Gauge
	MAX-ACCESS read-only
	STATUS current
	DESCRIPTION
		"The lifespan of the generated certificates for Client Certificate Constrained Delegation."
	::= { ltmServerSslEntry 45 }

ltmServerSslC3dCertExtensionIncludes OBJECT-TYPE
	SYNTAX Gauge
	MAX-ACCESS read-only
	STATUS current
	DESCRIPTION
		"The certificate extensions to include in generated certificates for
	        Client Certificate Constrained Delegation.
	        SSL_C3D_CERT_EXT_BASIC_CONSTRAINTS             = 2
	        SSL_C3D_CERT_EXT_EXTENDED_KEY_USAGE            = 16
	        SSL_C3D_CERT_EXT_KEY_USAGE                     = 128
	        SSL_C3D_CERT_EXT_SUBJECT_ALTERNATIVE_NAME      = 256"
	::= { ltmServerSslEntry 46 }

ltmServerSslData0rttMode OBJECT-TYPE
	SYNTAX INTEGER {
		false(0),
		true(1)
	}
	MAX-ACCESS read-only
	STATUS current
	DESCRIPTION
		"Specifies if TLSv1.3 should send 0-RTT early data when available."
	::= { ltmServerSslEntry 47 }

--==================================================================
-- Profile_serverssl_stat
--==================================================================
ltmServerSslStatResetStats OBJECT-TYPE
	SYNTAX INTEGER
	MAX-ACCESS read-write
	STATUS current
	DESCRIPTION
		"The action to reset resettable statistics data in ltmServerSslProfileStat.
		 Setting this value to 1 will reset statistics data.
		 Note, some statistics data may not be reset including data that are incremental counters."
	::= { ltmServerSslProfileStat 1 }

ltmServerSslStatNumber OBJECT-TYPE
	SYNTAX INTEGER
	MAX-ACCESS read-only
	STATUS current
	DESCRIPTION
		"The number of ltmServerSslProfileStat entries in the table."
	::= { ltmServerSslProfileStat 2 }

ltmServerSslStatTable OBJECT-TYPE
	SYNTAX SEQUENCE OF LtmServerSslStatEntry
	MAX-ACCESS not-accessible
	STATUS current
	DESCRIPTION
		"A table containing statistic information of the server-side SSL profiles.(BIG-IP acts as an SSL client)"
	::= { ltmServerSslProfileStat 3 }

ltmServerSslStatEntry OBJECT-TYPE
	SYNTAX  LtmServerSslStatEntry
	MAX-ACCESS not-accessible
	STATUS current
	DESCRIPTION
		"Columns in the ltmServerSslStat Table"
	INDEX {
		ltmServerSslStatName
	}
	::= { ltmServerSslStatTable 1 }

LtmServerSslStatEntry ::=
	SEQUENCE {
        	ltmServerSslStatName                                      LongDisplayString,
        	ltmServerSslStatCurConns                                  Gauge,
        	ltmServerSslStatMaxConns                                  Counter64,
        	ltmServerSslStatCurNativeConns                            Gauge,
        	ltmServerSslStatMaxNativeConns                            Counter64,
        	ltmServerSslStatTotNativeConns                            Counter64,
        	ltmServerSslStatCurCompatConns                            Gauge,
        	ltmServerSslStatMaxCompatConns                            Counter64,
        	ltmServerSslStatTotCompatConns                            Counter64,
        	ltmServerSslStatEncryptedBytesIn                          Counter64,
        	ltmServerSslStatEncryptedBytesOut                         Counter64,
        	ltmServerSslStatDecryptedBytesIn                          Counter64,
        	ltmServerSslStatDecryptedBytesOut                         Counter64,
        	ltmServerSslStatRecordsIn                                 Counter64,
        	ltmServerSslStatRecordsOut                                Counter64,
        	ltmServerSslStatFullyHwAcceleratedConns                   Counter64,
        	ltmServerSslStatPartiallyHwAcceleratedConns               Counter64,
        	ltmServerSslStatNonHwAcceleratedConns                     Counter64,
        	ltmServerSslStatPrematureDisconnects                      Counter64,
        	ltmServerSslStatMidstreamRenegotiations                   Counter64,
        	ltmServerSslStatSessCacheCurEntries                       Gauge,
        	ltmServerSslStatSessCacheHits                             Counter64,
        	ltmServerSslStatSessCacheLookups                          Counter64,
        	ltmServerSslStatSessCacheOverflows                        Counter64,
        	ltmServerSslStatSessCacheInvalidations                    Counter64,
        	ltmServerSslStatPeercertValid                             Counter64,
        	ltmServerSslStatPeercertInvalid                           Counter64,
        	ltmServerSslStatPeercertNone                              Counter64,
        	ltmServerSslStatHandshakeFailures                         Counter64,
        	ltmServerSslStatBadRecords                                Counter64,
        	ltmServerSslStatFatalAlerts                               Counter64,
        	ltmServerSslStatSslv2                                     Counter64,
        	ltmServerSslStatSslv3                                     Counter64,
        	ltmServerSslStatTlsv1                                     Counter64,
        	ltmServerSslStatAdhKeyxchg                                Counter64,
        	ltmServerSslStatDhDssKeyxchg                              Counter64,
        	ltmServerSslStatDhRsaKeyxchg                              Counter64,
        	ltmServerSslStatDssKeyxchg                                Counter64,
        	ltmServerSslStatEdhDssKeyxchg                             Counter64,
        	ltmServerSslStatRsaKeyxchg                                Counter64,
        	ltmServerSslStatNullBulk                                  Counter64,
        	ltmServerSslStatAesBulk                                   Counter64,
        	ltmServerSslStatDesBulk                                   Counter64,
        	ltmServerSslStatIdeaBulk                                  Counter64,
        	ltmServerSslStatRc2Bulk                                   Counter64,
        	ltmServerSslStatRc4Bulk                                   Counter64,
        	ltmServerSslStatNullDigest                                Counter64,
        	ltmServerSslStatMd5Digest                                 Counter64,
        	ltmServerSslStatShaDigest                                 Counter64,
        	ltmServerSslStatNotssl                                    Counter64,
        	ltmServerSslStatEdhRsaKeyxchg                             Counter64,
        	ltmServerSslStatSecureHandshakes                          Counter64,
        	ltmServerSslStatInsecureHandshakeAccepts                  Counter64,
        	ltmServerSslStatInsecureHandshakeRejects                  Counter64,
        	ltmServerSslStatInsecureRenegotiationRejects              Counter64,
        	ltmServerSslStatSniRejects                                Counter64,
        	ltmServerSslStatTlsv11                                    Counter64,
        	ltmServerSslStatTlsv12                                    Counter64,
        	ltmServerSslStatDtlsv1                                    Counter64,
        	ltmServerSslStatReused                                    Counter64,
        	ltmServerSslStatReuseFailed                               Counter64,
        	ltmServerSslStatEcdheRsaKeyxchg                           Counter64,
        	ltmServerSslStatConns                                     Counter64,
        	ltmServerSslStatEcdhRsaKeyxchg                            Counter64,
        	ltmServerSslStatEcdheEcdsaKeyxchg                         Counter64,
        	ltmServerSslStatEcdhEcdsaKeyxchg                          Counter64,
        	ltmServerSslStatDheDssKeyxchg                             Counter64,
        	ltmServerSslStatAesGcmBulk                                Counter64,
        	ltmServerSslStatDestinationIpBypasses                     Counter64,
        	ltmServerSslStatSourceIpBypasses                          Counter64,
        	ltmServerSslStatHostnameBypasses                          Counter64,
        	ltmServerSslStatSessionMirrorSuccess                      Counter64,
        	ltmServerSslStatSessionMirrorFailure                      Counter64,
        	ltmServerSslStatConnectionMirrorPeerReady                 Counter64,
        	ltmServerSslStatConnectionMirrorHaCtxSent                 Counter64,
        	ltmServerSslStatConnectionMirrorHaCtxRecv                 Counter64,
        	ltmServerSslStatConnectionMirrorHaHsSuccess               Counter64,
        	ltmServerSslStatConnectionMirrorHaFailure                 Counter64,
        	ltmServerSslStatConnectionMirrorHaTimeout                 Counter64,
        	ltmServerSslStatDtlsTxPushbacks                           Counter64,
        	ltmServerSslStatCamelliaBulk                              Counter64,
        	ltmServerSslStatActiveHandshakeRejected                   Counter64,
        	ltmServerSslStatCurrentActiveHandshakes                   Counter64,
        	ltmServerSslStatLicensedTps                               Counter64,
        	ltmServerSslStatExtendedMasterSecrets                     Counter64,
        	ltmServerSslStatOcspServersslCachedResp                   Counter64,
        	ltmServerSslStatOcspServersslStapledResp                  Counter64,
        	ltmServerSslStatOcspServersslResponderQueries             Counter64,
        	ltmServerSslStatOcspServersslResponseErrors               Counter64,
        	ltmServerSslStatOcspServersslCertStatusUnknown            Counter64,
        	ltmServerSslStatOcspServersslCertStatusRevoked            Counter64,
        	ltmServerSslStatC3dConns                                  Counter64,
        	ltmServerSslStatTlsv13                                    Counter64,
        	ltmServerSslStatChacha20Poly1305Bulk                      Counter64,
        	ltmServerSslStatAesBulkOffload                            Counter64,
        	ltmServerSslStatAesGcmBulkOffload                         Counter64,
        	ltmServerSslStatChacha20Poly1305BulkOffld                 Counter64,
        	ltmServerSslStatDesBulkOffload                            Counter64,
        	ltmServerSslStatRc4BulkOffload                            Counter64,
        	ltmServerSslStatCamelliaBulkOffload                       Counter64,
        	ltmServerSslStatMd5DigestOffload                          Counter64,
        	ltmServerSslStatShaDigestOffload                          Counter64,
        	ltmServerSslStatSha224Digest                              Counter64,
        	ltmServerSslStatSha224DigestOffload                       Counter64,
        	ltmServerSslStatSha256Digest                              Counter64,
        	ltmServerSslStatSha256DigestOffload                       Counter64,
        	ltmServerSslStatSha384Digest                              Counter64,
        	ltmServerSslStatSha384DigestOffload                       Counter64,
        	ltmServerSslStatSha512Digest                              Counter64,
        	ltmServerSslStatSha512DigestOffload                       Counter64,
        	ltmServerSslStatDhGroupP256                               Counter64,
        	ltmServerSslStatDhGroupP256Offload                        Counter64,
        	ltmServerSslStatDhGroupP384                               Counter64,
        	ltmServerSslStatDhGroupP384Offload                        Counter64,
        	ltmServerSslStatDhGroupX25519                             Counter64,
        	ltmServerSslStatDhGroupX25519Offload                      Counter64,
        	ltmServerSslStatRsaKeySize1024                            Counter64,
        	ltmServerSslStatRsaKeySize1024Offload                     Counter64,
        	ltmServerSslStatRsaKeySize2048                            Counter64,
        	ltmServerSslStatRsaKeySize2048Offload                     Counter64,
        	ltmServerSslStatRsaKeySize4096                            Counter64,
        	ltmServerSslStatRsaKeySize4096Offload                     Counter64,
        	ltmServerSslStatTotalHandshakesSoftware                   Counter64,
        	ltmServerSslStatTotalHandshakesOffload                    Counter64
	}

ltmServerSslStatName OBJECT-TYPE
	SYNTAX LongDisplayString
	MAX-ACCESS read-only
	STATUS current
	DESCRIPTION
		"The name of a server-side SSL profile."
	::= { ltmServerSslStatEntry 1 }

ltmServerSslStatCurConns OBJECT-TYPE
	SYNTAX Gauge
	MAX-ACCESS read-only
	STATUS current
	DESCRIPTION
		"The current number of concurrent connections with
		 established SSL sessions being maintained by the filter."
	::= { ltmServerSslStatEntry 2 }

ltmServerSslStatMaxConns OBJECT-TYPE
	SYNTAX Counter64
	MAX-ACCESS read-only
	STATUS current
	DESCRIPTION
		"The maximum number of concurrent connections with
		 established SSL sessions being maintained by the filter."
	::= { ltmServerSslStatEntry 3 }

ltmServerSslStatCurNativeConns OBJECT-TYPE
	SYNTAX Gauge
	MAX-ACCESS read-only
	STATUS current
	DESCRIPTION
		"The current number of concurrent native connections with
		 established SSL sessions being maintained by the filter."
	::= { ltmServerSslStatEntry 4 }

ltmServerSslStatMaxNativeConns OBJECT-TYPE
	SYNTAX Counter64
	MAX-ACCESS read-only
	STATUS current
	DESCRIPTION
		"The maximum number of concurrent native connections with
		 established SSL sessions being maintained by the filter."
	::= { ltmServerSslStatEntry 5 }

ltmServerSslStatTotNativeConns OBJECT-TYPE
	SYNTAX Counter64
	MAX-ACCESS read-only
	STATUS current
	DESCRIPTION
		"The total number of concurrent native connections with
		 established SSL sessions being maintained by the filter."
	::= { ltmServerSslStatEntry 6 }

ltmServerSslStatCurCompatConns OBJECT-TYPE
	SYNTAX Gauge
	MAX-ACCESS read-only
	STATUS current
	DESCRIPTION
		"The current number of concurrent compat connections with
		 established SSL sessions being maintained by the filter."
	::= { ltmServerSslStatEntry 7 }

ltmServerSslStatMaxCompatConns OBJECT-TYPE
	SYNTAX Counter64
	MAX-ACCESS read-only
	STATUS current
	DESCRIPTION
		"The maximum number of concurrent compat connections with
		 established SSL sessions being maintained by the filter."
	::= { ltmServerSslStatEntry 8 }

ltmServerSslStatTotCompatConns OBJECT-TYPE
	SYNTAX Counter64
	MAX-ACCESS read-only
	STATUS current
	DESCRIPTION
		"The total number of concurrent compat connections with
		 established SSL sessions being maintained by the filter."
	::= { ltmServerSslStatEntry 9 }

ltmServerSslStatEncryptedBytesIn OBJECT-TYPE
	SYNTAX Counter64
	MAX-ACCESS read-only
	STATUS current
	DESCRIPTION
		"The total encrypted bytes received."
	::= { ltmServerSslStatEntry 10 }

ltmServerSslStatEncryptedBytesOut OBJECT-TYPE
	SYNTAX Counter64
	MAX-ACCESS read-only
	STATUS current
	DESCRIPTION
		"The total encrypted bytes sent."
	::= { ltmServerSslStatEntry 11 }

ltmServerSslStatDecryptedBytesIn OBJECT-TYPE
	SYNTAX Counter64
	MAX-ACCESS read-only
	STATUS current
	DESCRIPTION
		"The total decrypted bytes received."
	::= { ltmServerSslStatEntry 12 }

ltmServerSslStatDecryptedBytesOut OBJECT-TYPE
	SYNTAX Counter64
	MAX-ACCESS read-only
	STATUS current
	DESCRIPTION
		"The total decrypted bytes sent."
	::= { ltmServerSslStatEntry 13 }

ltmServerSslStatRecordsIn OBJECT-TYPE
	SYNTAX Counter64
	MAX-ACCESS read-only
	STATUS current
	DESCRIPTION
		"The total records received."
	::= { ltmServerSslStatEntry 14 }

ltmServerSslStatRecordsOut OBJECT-TYPE
	SYNTAX Counter64
	MAX-ACCESS read-only
	STATUS current
	DESCRIPTION
		"The total records sent."
	::= { ltmServerSslStatEntry 15 }

ltmServerSslStatFullyHwAcceleratedConns OBJECT-TYPE
	SYNTAX Counter64
	MAX-ACCESS read-only
	STATUS current
	DESCRIPTION
		"Fully hardware-accelerated implies usage of the Cavium
		 Nitrox or similar hardware accelerator such that all
		 significant cryptographic operations are offloaded,
		 including but not limited to the SSL handshake (at least
		 the RSA/DSA/DH operations) and record processing (at least
		 the bulk cipher plus MAC)."
	::= { ltmServerSslStatEntry 16 }

ltmServerSslStatPartiallyHwAcceleratedConns OBJECT-TYPE
	SYNTAX Counter64
	MAX-ACCESS read-only
	STATUS current
	DESCRIPTION
		"Partially hardware-accelerated indicates that at least the
		 RSA decryptions are offloaded."
	::= { ltmServerSslStatEntry 17 }

ltmServerSslStatNonHwAcceleratedConns OBJECT-TYPE
	SYNTAX Counter64
	MAX-ACCESS read-only
	STATUS current
	DESCRIPTION
		"Non-accelerated connections are those for which no
		 steady-state hardware acceleration is available (either
		 because no hardware accelerators are available or because
		 the necessary cryptographic operations are unsupported).
		 Because the extent of hardware acceleration may not be known
		 until a connection has closed (mid-stream SSL handshakes
		 might renegotiate an SSL session not supported by hardware
		 acceleration), this statistic will not be updated for a
		 given connection until it has closed."
	::= { ltmServerSslStatEntry 18 }

ltmServerSslStatPrematureDisconnects OBJECT-TYPE
	SYNTAX Counter64
	MAX-ACCESS read-only
	STATUS current
	DESCRIPTION
		"The number of connections disconnected before SSL session
		 establishment: the total number of connections that were
		 prematurely closed before an SSL session was established,
		 not including connections in pass-through mode."
	::= { ltmServerSslStatEntry 19 }

ltmServerSslStatMidstreamRenegotiations OBJECT-TYPE
	SYNTAX Counter64
	MAX-ACCESS read-only
	STATUS current
	DESCRIPTION
		"The number of mid-stream SSL re-negotiations, not including
		 initial SSL session establishment."
	::= { ltmServerSslStatEntry 20 }

ltmServerSslStatSessCacheCurEntries OBJECT-TYPE
	SYNTAX Gauge
	MAX-ACCESS read-only
	STATUS current
	DESCRIPTION
		"The number of the current entries in this cache."
	::= { ltmServerSslStatEntry 21 }

ltmServerSslStatSessCacheHits OBJECT-TYPE
	SYNTAX Counter64
	MAX-ACCESS read-only
	STATUS current
	DESCRIPTION
		"The total number of the cache hits."
	::= { ltmServerSslStatEntry 22 }

ltmServerSslStatSessCacheLookups OBJECT-TYPE
	SYNTAX Counter64
	MAX-ACCESS read-only
	STATUS current
	DESCRIPTION
		"The total number of the cache lookups."
	::= { ltmServerSslStatEntry 23 }

ltmServerSslStatSessCacheOverflows OBJECT-TYPE
	SYNTAX Counter64
	MAX-ACCESS read-only
	STATUS current
	DESCRIPTION
		"The total number of the cache overflows."
	::= { ltmServerSslStatEntry 24 }

ltmServerSslStatSessCacheInvalidations OBJECT-TYPE
	SYNTAX Counter64
	MAX-ACCESS read-only
	STATUS current
	DESCRIPTION
		"The total number of the session invalidations."
	::= { ltmServerSslStatEntry 25 }

ltmServerSslStatPeercertValid OBJECT-TYPE
	SYNTAX Counter64
	MAX-ACCESS read-only
	STATUS current
	DESCRIPTION
		"The total number of the valid certificates."
	::= { ltmServerSslStatEntry 26 }

ltmServerSslStatPeercertInvalid OBJECT-TYPE
	SYNTAX Counter64
	MAX-ACCESS read-only
	STATUS current
	DESCRIPTION
		"The total number of the invalid certificates."
	::= { ltmServerSslStatEntry 27 }

ltmServerSslStatPeercertNone OBJECT-TYPE
	SYNTAX Counter64
	MAX-ACCESS read-only
	STATUS current
	DESCRIPTION
		"The total number of connections without certificates."
	::= { ltmServerSslStatEntry 28 }

ltmServerSslStatHandshakeFailures OBJECT-TYPE
	SYNTAX Counter64
	MAX-ACCESS read-only
	STATUS current
	DESCRIPTION
		"The total number of handshake failures."
	::= { ltmServerSslStatEntry 29 }

ltmServerSslStatBadRecords OBJECT-TYPE
	SYNTAX Counter64
	MAX-ACCESS read-only
	STATUS current
	DESCRIPTION
		"The total number of the bad records."
	::= { ltmServerSslStatEntry 30 }

ltmServerSslStatFatalAlerts OBJECT-TYPE
	SYNTAX Counter64
	MAX-ACCESS read-only
	STATUS current
	DESCRIPTION
		"The total number of the fatal alerts."
	::= { ltmServerSslStatEntry 31 }

ltmServerSslStatSslv2 OBJECT-TYPE
	SYNTAX Counter64
	MAX-ACCESS read-only
	STATUS current
	DESCRIPTION
		"The total connections for SSL protocol version 2."
	::= { ltmServerSslStatEntry 32 }

ltmServerSslStatSslv3 OBJECT-TYPE
	SYNTAX Counter64
	MAX-ACCESS read-only
	STATUS current
	DESCRIPTION
		"The total connections for SSL protocol version 3."
	::= { ltmServerSslStatEntry 33 }

ltmServerSslStatTlsv1 OBJECT-TYPE
	SYNTAX Counter64
	MAX-ACCESS read-only
	STATUS current
	DESCRIPTION
		"The total connections for SSL TLS protocol version 1."
	::= { ltmServerSslStatEntry 34 }

ltmServerSslStatAdhKeyxchg OBJECT-TYPE
	SYNTAX Counter64
	MAX-ACCESS read-only
	STATUS current
	DESCRIPTION
		"The anonymous Diffie-Hellman."
	::= { ltmServerSslStatEntry 35 }

ltmServerSslStatDhDssKeyxchg OBJECT-TYPE
	SYNTAX Counter64
	MAX-ACCESS read-only
	STATUS	 deprecated
	DESCRIPTION
		"Deprecated! DSS certificate is obsolete in BIGIP.
		The diffie-Hellman w/ DSS certificate."
	::= { ltmServerSslStatEntry 36 }

ltmServerSslStatDhRsaKeyxchg OBJECT-TYPE
	SYNTAX Counter64
	MAX-ACCESS read-only
	STATUS current
	DESCRIPTION
		"The diffie-Hellman w/ RSA certificate."
	::= { ltmServerSslStatEntry 37 }

ltmServerSslStatDssKeyxchg OBJECT-TYPE
	SYNTAX Counter64
	MAX-ACCESS read-only
	STATUS	 deprecated
	DESCRIPTION
		"Deprecated! DSS certificate is obsolete in BIGIP.
		The DSS certificate."
	::= { ltmServerSslStatEntry 38 }

ltmServerSslStatEdhDssKeyxchg OBJECT-TYPE
	SYNTAX Counter64
	MAX-ACCESS read-only
	STATUS	 deprecated
	DESCRIPTION
		"Deprecated! DSS certificate is obsolete in BIGIP.
		The ephemeral Diffie-Hellman w/ DSS cert."
	::= { ltmServerSslStatEntry 39 }

ltmServerSslStatRsaKeyxchg OBJECT-TYPE
	SYNTAX Counter64
	MAX-ACCESS read-only
	STATUS current
	DESCRIPTION
		"The RSA certificate."
	::= { ltmServerSslStatEntry 40 }

ltmServerSslStatNullBulk OBJECT-TYPE
	SYNTAX Counter64
	MAX-ACCESS read-only
	STATUS current
	DESCRIPTION
		"No encryption."
	::= { ltmServerSslStatEntry 41 }

ltmServerSslStatAesBulk OBJECT-TYPE
	SYNTAX Counter64
	MAX-ACCESS read-only
	STATUS current
	DESCRIPTION
		"Advanced Encryption Standard (CBC)."
	::= { ltmServerSslStatEntry 42 }

ltmServerSslStatDesBulk OBJECT-TYPE
	SYNTAX Counter64
	MAX-ACCESS read-only
	STATUS current
	DESCRIPTION
		"Digital Encryption Standard (CBC)."
	::= { ltmServerSslStatEntry 43 }

ltmServerSslStatIdeaBulk OBJECT-TYPE
	SYNTAX Counter64
	MAX-ACCESS read-only
	STATUS current
	DESCRIPTION
		"IDEA (old SSLv2 cipher)."
	::= { ltmServerSslStatEntry 44 }

ltmServerSslStatRc2Bulk OBJECT-TYPE
	SYNTAX Counter64
	MAX-ACCESS read-only
	STATUS current
	DESCRIPTION
		"Rivest Cipher 2 (CBC)."
	::= { ltmServerSslStatEntry 45 }

ltmServerSslStatRc4Bulk OBJECT-TYPE
	SYNTAX Counter64
	MAX-ACCESS read-only
	STATUS current
	DESCRIPTION
		"Rivest Cipher 4 (CBC)."
	::= { ltmServerSslStatEntry 46 }

ltmServerSslStatNullDigest OBJECT-TYPE
	SYNTAX Counter64
	MAX-ACCESS read-only
	STATUS current
	DESCRIPTION
		"No message authentication."
	::= { ltmServerSslStatEntry 47 }

ltmServerSslStatMd5Digest OBJECT-TYPE
	SYNTAX Counter64
	MAX-ACCESS read-only
	STATUS current
	DESCRIPTION
		"Message Digest 5."
	::= { ltmServerSslStatEntry 48 }

ltmServerSslStatShaDigest OBJECT-TYPE
	SYNTAX Counter64
	MAX-ACCESS read-only
	STATUS current
	DESCRIPTION
		"Secure Hash Algorithm."
	::= { ltmServerSslStatEntry 49 }

ltmServerSslStatNotssl OBJECT-TYPE
	SYNTAX Counter64
	MAX-ACCESS read-only
	STATUS current
	DESCRIPTION
		"The total number of the bad client greetings."
	::= { ltmServerSslStatEntry 50 }

ltmServerSslStatEdhRsaKeyxchg OBJECT-TYPE
	SYNTAX Counter64
	MAX-ACCESS read-only
	STATUS current
	DESCRIPTION
		"Ephemeral Diffie-Hellman w/ RSA cert."
	::= { ltmServerSslStatEntry 51 }

ltmServerSslStatSecureHandshakes OBJECT-TYPE
	SYNTAX Counter64
	MAX-ACCESS read-only
	STATUS current
	DESCRIPTION
		"The number of handshakes, including mid-stream re-negotiations,
	         performed with peers supporting SSL secure renegotiation."
	::= { ltmServerSslStatEntry 52 }

ltmServerSslStatInsecureHandshakeAccepts OBJECT-TYPE
	SYNTAX Counter64
	MAX-ACCESS read-only
	STATUS current
	DESCRIPTION
		"The number of handshakes, including mid-stream re-negotiations,
	         performed with peers not supporting SSL secure renegotiation."
	::= { ltmServerSslStatEntry 53 }

ltmServerSslStatInsecureHandshakeRejects OBJECT-TYPE
	SYNTAX Counter64
	MAX-ACCESS read-only
	STATUS current
	DESCRIPTION
		"The number of rejected initial handshakes with peers
	         not supporting SSL secure renegotiation."
	::= { ltmServerSslStatEntry 54 }

ltmServerSslStatInsecureRenegotiationRejects OBJECT-TYPE
	SYNTAX Counter64
	MAX-ACCESS read-only
	STATUS current
	DESCRIPTION
		"The number of rejected renegotiation attempts by peers
	         not supporting SSL secure renegotiation."
	::= { ltmServerSslStatEntry 55 }

ltmServerSslStatSniRejects OBJECT-TYPE
	SYNTAX Counter64
	MAX-ACCESS read-only
	STATUS current
	DESCRIPTION
		"The number of rejected handshake attempts by peers
	         not supporting SSL SNI extension or having mismatched
	         server names."
	::= { ltmServerSslStatEntry 56 }

ltmServerSslStatTlsv11 OBJECT-TYPE
	SYNTAX Counter64
	MAX-ACCESS read-only
	STATUS current
	DESCRIPTION
		"The total connections for SSL TLS protocol version 1.1."
	::= { ltmServerSslStatEntry 57 }

ltmServerSslStatTlsv12 OBJECT-TYPE
	SYNTAX Counter64
	MAX-ACCESS read-only
	STATUS current
	DESCRIPTION
		"The total connections for SSL TLS protocol version 1.2."
	::= { ltmServerSslStatEntry 58 }

ltmServerSslStatDtlsv1 OBJECT-TYPE
	SYNTAX Counter64
	MAX-ACCESS read-only
	STATUS current
	DESCRIPTION
		"The total connections for SSL DTLS protocol version 1."
	::= { ltmServerSslStatEntry 59 }

ltmServerSslStatReused OBJECT-TYPE
	SYNTAX Counter64
	MAX-ACCESS read-only
	STATUS current
	DESCRIPTION
		"The total reused session ticket sessions."
	::= { ltmServerSslStatEntry 60 }

ltmServerSslStatReuseFailed OBJECT-TYPE
	SYNTAX Counter64
	MAX-ACCESS read-only
	STATUS current
	DESCRIPTION
		"The total failed reused session ticket sessions."
	::= { ltmServerSslStatEntry 61 }

ltmServerSslStatEcdheRsaKeyxchg OBJECT-TYPE
	SYNTAX Counter64
	MAX-ACCESS read-only
	STATUS current
	DESCRIPTION
		"Ephemeral ECDH w/ RSA cert."
	::= { ltmServerSslStatEntry 62 }

ltmServerSslStatConns OBJECT-TYPE
	SYNTAX Counter64
	MAX-ACCESS read-only
	STATUS current
	DESCRIPTION
		"The total connections using SSL FWDP feature."
	::= { ltmServerSslStatEntry 63 }

ltmServerSslStatEcdhRsaKeyxchg OBJECT-TYPE
	SYNTAX Counter64
	MAX-ACCESS read-only
	STATUS current
	DESCRIPTION
		"Fixed ECDH with RSA signed cert."
	::= { ltmServerSslStatEntry 64 }

ltmServerSslStatEcdheEcdsaKeyxchg OBJECT-TYPE
	SYNTAX Counter64
	MAX-ACCESS read-only
	STATUS current
	DESCRIPTION
		"Ephemeral ECDH with ECDSA cert."
	::= { ltmServerSslStatEntry 65 }

ltmServerSslStatEcdhEcdsaKeyxchg OBJECT-TYPE
	SYNTAX Counter64
	MAX-ACCESS read-only
	STATUS current
	DESCRIPTION
		"Fixed ECDH with ECDSA cert."
	::= { ltmServerSslStatEntry 66 }

ltmServerSslStatDheDssKeyxchg OBJECT-TYPE
	SYNTAX Counter64
	MAX-ACCESS read-only
	STATUS current
	DESCRIPTION
		"Ephemeral DH with DSS cert."
	::= { ltmServerSslStatEntry 67 }

ltmServerSslStatAesGcmBulk OBJECT-TYPE
	SYNTAX Counter64
	MAX-ACCESS read-only
	STATUS current
	DESCRIPTION
		"Advanced Encryption Standard Galois Counter Mode (AES-GCM)."
	::= { ltmServerSslStatEntry 68 }

ltmServerSslStatDestinationIpBypasses OBJECT-TYPE
	SYNTAX Counter64
	MAX-ACCESS read-only
	STATUS current
	DESCRIPTION
		"The total destination IP bypasses using SSL FWDP bypass feature."
	::= { ltmServerSslStatEntry 69 }

ltmServerSslStatSourceIpBypasses OBJECT-TYPE
	SYNTAX Counter64
	MAX-ACCESS read-only
	STATUS current
	DESCRIPTION
		"The total source IP bypasses using SSL FWDP bypass feature."
	::= { ltmServerSslStatEntry 70 }

ltmServerSslStatHostnameBypasses OBJECT-TYPE
	SYNTAX Counter64
	MAX-ACCESS read-only
	STATUS current
	DESCRIPTION
		"The total hostname bypasses using SSL FWDP bypass feature."
	::= { ltmServerSslStatEntry 71 }

ltmServerSslStatSessionMirrorSuccess OBJECT-TYPE
	SYNTAX Counter64
	MAX-ACCESS read-only
	STATUS current
	DESCRIPTION
		"The total SSL sessions mirrored successfully."
	::= { ltmServerSslStatEntry 72 }

ltmServerSslStatSessionMirrorFailure OBJECT-TYPE
	SYNTAX Counter64
	MAX-ACCESS read-only
	STATUS current
	DESCRIPTION
		"The total SSL session mirror failures."
	::= { ltmServerSslStatEntry 73 }

ltmServerSslStatConnectionMirrorPeerReady OBJECT-TYPE
	SYNTAX Counter64
	MAX-ACCESS read-only
	STATUS current
	DESCRIPTION
		"The total SSL HA peer ready messages."
	::= { ltmServerSslStatEntry 74 }

ltmServerSslStatConnectionMirrorHaCtxSent OBJECT-TYPE
	SYNTAX Counter64
	MAX-ACCESS read-only
	STATUS current
	DESCRIPTION
		"The total SSL HA context sent messages."
	::= { ltmServerSslStatEntry 75 }

ltmServerSslStatConnectionMirrorHaCtxRecv OBJECT-TYPE
	SYNTAX Counter64
	MAX-ACCESS read-only
	STATUS current
	DESCRIPTION
		"The total SSL HA context received messages."
	::= { ltmServerSslStatEntry 76 }

ltmServerSslStatConnectionMirrorHaHsSuccess OBJECT-TYPE
	SYNTAX Counter64
	MAX-ACCESS read-only
	STATUS current
	DESCRIPTION
		"The total SSL HA handshake succesful."
	::= { ltmServerSslStatEntry 77 }

ltmServerSslStatConnectionMirrorHaFailure OBJECT-TYPE
	SYNTAX Counter64
	MAX-ACCESS read-only
	STATUS current
	DESCRIPTION
		"The total SSL HA failures."
	::= { ltmServerSslStatEntry 78 }

ltmServerSslStatConnectionMirrorHaTimeout OBJECT-TYPE
	SYNTAX Counter64
	MAX-ACCESS read-only
	STATUS current
	DESCRIPTION
		"The total SSL HA timeouts."
	::= { ltmServerSslStatEntry 79 }

ltmServerSslStatDtlsTxPushbacks OBJECT-TYPE
	SYNTAX Counter64
	MAX-ACCESS read-only
	STATUS current
	DESCRIPTION
		"The total number of the Datagram Transport Layer Security transmitted packets which are pushed back."
	::= { ltmServerSslStatEntry 80 }

ltmServerSslStatCamelliaBulk OBJECT-TYPE
	SYNTAX Counter64
	MAX-ACCESS read-only
	STATUS current
	DESCRIPTION
		"Camellia Cipher (CBC)."
	::= { ltmServerSslStatEntry 81 }

ltmServerSslStatActiveHandshakeRejected OBJECT-TYPE
	SYNTAX Counter64
	MAX-ACCESS read-only
	STATUS current
	DESCRIPTION
		"The total number of active handshakes rejected."
	::= { ltmServerSslStatEntry 82 }

ltmServerSslStatCurrentActiveHandshakes OBJECT-TYPE
	SYNTAX Counter64
	MAX-ACCESS read-only
	STATUS current
	DESCRIPTION
		"The total number of current active handshakes."
	::= { ltmServerSslStatEntry 83 }

ltmServerSslStatLicensedTps OBJECT-TYPE
	SYNTAX Counter64
	MAX-ACCESS read-only
	STATUS current
	DESCRIPTION
		"The licensed transactions per second (TPS) value."
	::= { ltmServerSslStatEntry 84 }

ltmServerSslStatExtendedMasterSecrets OBJECT-TYPE
	SYNTAX Counter64
	MAX-ACCESS read-only
	STATUS current
	DESCRIPTION
		"The total number of extended master secret handshakes."
	::= { ltmServerSslStatEntry 85 }

ltmServerSslStatOcspServersslCachedResp OBJECT-TYPE
	SYNTAX Counter64
	MAX-ACCESS read-only
	STATUS current
	DESCRIPTION
		"Total number of server connections for which OCSP response was obtained from the cache."
	::= { ltmServerSslStatEntry 86 }

ltmServerSslStatOcspServersslStapledResp OBJECT-TYPE
	SYNTAX Counter64
	MAX-ACCESS read-only
	STATUS current
	DESCRIPTION
		"Total number of server connections that had stapled a valid OCSP response."
	::= { ltmServerSslStatEntry 87 }

ltmServerSslStatOcspServersslResponderQueries OBJECT-TYPE
	SYNTAX Counter64
	MAX-ACCESS read-only
	STATUS current
	DESCRIPTION
		"Total number of server connections that required communicating with OCSP responder."
	::= { ltmServerSslStatEntry 88 }

ltmServerSslStatOcspServersslResponseErrors OBJECT-TYPE
	SYNTAX Counter64
	MAX-ACCESS read-only
	STATUS current
	DESCRIPTION
		"Total number of server connections for which OCSP responder query failed for any reason."
	::= { ltmServerSslStatEntry 89 }

ltmServerSslStatOcspServersslCertStatusUnknown OBJECT-TYPE
	SYNTAX Counter64
	MAX-ACCESS read-only
	STATUS current
	DESCRIPTION
		"Total number of server connections for which certificate status was indicated as unknown."
	::= { ltmServerSslStatEntry 90 }

ltmServerSslStatOcspServersslCertStatusRevoked OBJECT-TYPE
	SYNTAX Counter64
	MAX-ACCESS read-only
	STATUS current
	DESCRIPTION
		"Total number of server connections for which certificate status was indicated as revoked."
	::= { ltmServerSslStatEntry 91 }

ltmServerSslStatC3dConns OBJECT-TYPE
	SYNTAX Counter64
	MAX-ACCESS read-only
	STATUS current
	DESCRIPTION
		"The total connections using SSL C3D feature."
	::= { ltmServerSslStatEntry 92 }

ltmServerSslStatTlsv13 OBJECT-TYPE
	SYNTAX Counter64
	MAX-ACCESS read-only
	STATUS current
	DESCRIPTION
		"The total connections for SSL TLS protocol version 1.3."
	::= { ltmServerSslStatEntry 93 }

ltmServerSslStatChacha20Poly1305Bulk OBJECT-TYPE
	SYNTAX Counter64
	MAX-ACCESS read-only
	STATUS current
	DESCRIPTION
		"ChaCha20-Poly1305."
	::= { ltmServerSslStatEntry 94 }

ltmServerSslStatAesBulkOffload OBJECT-TYPE
	SYNTAX Counter64
	MAX-ACCESS read-only
	STATUS current
	DESCRIPTION
		"Advanced Encryption Standard (CBC) offload."
	::= { ltmServerSslStatEntry 95 }

ltmServerSslStatAesGcmBulkOffload OBJECT-TYPE
	SYNTAX Counter64
	MAX-ACCESS read-only
	STATUS current
	DESCRIPTION
		"Advanced Encryption Standard Galois Counter Mode (AES-GCM) offload."
	::= { ltmServerSslStatEntry 96 }

ltmServerSslStatChacha20Poly1305BulkOffld OBJECT-TYPE
	SYNTAX Counter64
	MAX-ACCESS read-only
	STATUS current
	DESCRIPTION
		"ChaCha20-Poly1305 offload."
	::= { ltmServerSslStatEntry 97 }

ltmServerSslStatDesBulkOffload OBJECT-TYPE
	SYNTAX Counter64
	MAX-ACCESS read-only
	STATUS current
	DESCRIPTION
		"Digital Encryption Standard (CBC) offload."
	::= { ltmServerSslStatEntry 98 }

ltmServerSslStatRc4BulkOffload OBJECT-TYPE
	SYNTAX Counter64
	MAX-ACCESS read-only
	STATUS current
	DESCRIPTION
		"Rivest Cipher 4 (CBC) offload."
	::= { ltmServerSslStatEntry 99 }

ltmServerSslStatCamelliaBulkOffload OBJECT-TYPE
	SYNTAX Counter64
	MAX-ACCESS read-only
	STATUS current
	DESCRIPTION
		"Camellia Cipher (CBC) offload."
	::= { ltmServerSslStatEntry 100 }

ltmServerSslStatMd5DigestOffload OBJECT-TYPE
	SYNTAX Counter64
	MAX-ACCESS read-only
	STATUS current
	DESCRIPTION
		"Message Digest 5 offload."
	::= { ltmServerSslStatEntry 101 }

ltmServerSslStatShaDigestOffload OBJECT-TYPE
	SYNTAX Counter64
	MAX-ACCESS read-only
	STATUS current
	DESCRIPTION
		"Secure Hash Algorithm offload."
	::= { ltmServerSslStatEntry 102 }

ltmServerSslStatSha224Digest OBJECT-TYPE
	SYNTAX Counter64
	MAX-ACCESS read-only
	STATUS current
	DESCRIPTION
		"Secure Hash Algorithm 224."
	::= { ltmServerSslStatEntry 103 }

ltmServerSslStatSha224DigestOffload OBJECT-TYPE
	SYNTAX Counter64
	MAX-ACCESS read-only
	STATUS current
	DESCRIPTION
		"Secure Hash Algorithm 224 offload."
	::= { ltmServerSslStatEntry 104 }

ltmServerSslStatSha256Digest OBJECT-TYPE
	SYNTAX Counter64
	MAX-ACCESS read-only
	STATUS current
	DESCRIPTION
		"Secure Hash Algorithm 256."
	::= { ltmServerSslStatEntry 105 }

ltmServerSslStatSha256DigestOffload OBJECT-TYPE
	SYNTAX Counter64
	MAX-ACCESS read-only
	STATUS current
	DESCRIPTION
		"Secure Hash Algorithm 256 offload."
	::= { ltmServerSslStatEntry 106 }

ltmServerSslStatSha384Digest OBJECT-TYPE
	SYNTAX Counter64
	MAX-ACCESS read-only
	STATUS current
	DESCRIPTION
		"Secure Hash Algorithm 384."
	::= { ltmServerSslStatEntry 107 }

ltmServerSslStatSha384DigestOffload OBJECT-TYPE
	SYNTAX Counter64
	MAX-ACCESS read-only
	STATUS current
	DESCRIPTION
		"Secure Hash Algorithm 384 offload."
	::= { ltmServerSslStatEntry 108 }

ltmServerSslStatSha512Digest OBJECT-TYPE
	SYNTAX Counter64
	MAX-ACCESS read-only
	STATUS current
	DESCRIPTION
		"Secure Hash Algorithm 512."
	::= { ltmServerSslStatEntry 109 }

ltmServerSslStatSha512DigestOffload OBJECT-TYPE
	SYNTAX Counter64
	MAX-ACCESS read-only
	STATUS current
	DESCRIPTION
		"Secure Hash Algorithm 512 offload."
	::= { ltmServerSslStatEntry 110 }

ltmServerSslStatDhGroupP256 OBJECT-TYPE
	SYNTAX Counter64
	MAX-ACCESS read-only
	STATUS current
	DESCRIPTION
		"DH Group P256."
	::= { ltmServerSslStatEntry 111 }

ltmServerSslStatDhGroupP256Offload OBJECT-TYPE
	SYNTAX Counter64
	MAX-ACCESS read-only
	STATUS current
	DESCRIPTION
		"DH Group P256 offload."
	::= { ltmServerSslStatEntry 112 }

ltmServerSslStatDhGroupP384 OBJECT-TYPE
	SYNTAX Counter64
	MAX-ACCESS read-only
	STATUS current
	DESCRIPTION
		"DH Group P384."
	::= { ltmServerSslStatEntry 113 }

ltmServerSslStatDhGroupP384Offload OBJECT-TYPE
	SYNTAX Counter64
	MAX-ACCESS read-only
	STATUS current
	DESCRIPTION
		"DH Group P384 offload."
	::= { ltmServerSslStatEntry 114 }

ltmServerSslStatDhGroupX25519 OBJECT-TYPE
	SYNTAX Counter64
	MAX-ACCESS read-only
	STATUS current
	DESCRIPTION
		"DH Group X25519."
	::= { ltmServerSslStatEntry 115 }

ltmServerSslStatDhGroupX25519Offload OBJECT-TYPE
	SYNTAX Counter64
	MAX-ACCESS read-only
	STATUS current
	DESCRIPTION
		"DH Group X25519 offload."
	::= { ltmServerSslStatEntry 116 }

ltmServerSslStatRsaKeySize1024 OBJECT-TYPE
	SYNTAX Counter64
	MAX-ACCESS read-only
	STATUS current
	DESCRIPTION
		"RSA key size 1024."
	::= { ltmServerSslStatEntry 117 }

ltmServerSslStatRsaKeySize1024Offload OBJECT-TYPE
	SYNTAX Counter64
	MAX-ACCESS read-only
	STATUS current
	DESCRIPTION
		"RSA key size 1024 offload."
	::= { ltmServerSslStatEntry 118 }

ltmServerSslStatRsaKeySize2048 OBJECT-TYPE
	SYNTAX Counter64
	MAX-ACCESS read-only
	STATUS current
	DESCRIPTION
		"RSA key size 2048."
	::= { ltmServerSslStatEntry 119 }

ltmServerSslStatRsaKeySize2048Offload OBJECT-TYPE
	SYNTAX Counter64
	MAX-ACCESS read-only
	STATUS current
	DESCRIPTION
		"RSA key size 2048_offload."
	::= { ltmServerSslStatEntry 120 }

ltmServerSslStatRsaKeySize4096 OBJECT-TYPE
	SYNTAX Counter64
	MAX-ACCESS read-only
	STATUS current
	DESCRIPTION
		"RSA key size 4096."
	::= { ltmServerSslStatEntry 121 }

ltmServerSslStatRsaKeySize4096Offload OBJECT-TYPE
	SYNTAX Counter64
	MAX-ACCESS read-only
	STATUS current
	DESCRIPTION
		"RSA key size 4096 offload."
	::= { ltmServerSslStatEntry 122 }

ltmServerSslStatTotalHandshakesSoftware OBJECT-TYPE
	SYNTAX Counter64
	MAX-ACCESS read-only
	STATUS current
	DESCRIPTION
		"Handshake records processed in software."
	::= { ltmServerSslStatEntry 123 }

ltmServerSslStatTotalHandshakesOffload OBJECT-TYPE
	SYNTAX Counter64
	MAX-ACCESS read-only
	STATUS current
	DESCRIPTION
		"Handshake records offloaded."
	::= { ltmServerSslStatEntry 124 }

--==================================================================
-- Profile_connpool
--==================================================================
ltmConnPoolProfileNumber OBJECT-TYPE
	SYNTAX INTEGER
	MAX-ACCESS read-only
	STATUS current
	DESCRIPTION
		"The number of ltmConnPoolProfile entries in the table."
	::= { ltmConnPoolProfile 1 }

ltmConnPoolProfileTable OBJECT-TYPE
	SYNTAX SEQUENCE OF LtmConnPoolProfileEntry
	MAX-ACCESS not-accessible
	STATUS current
	DESCRIPTION
		"A table containing information of connection pool profiles."
	::= { ltmConnPoolProfile 2 }

ltmConnPoolProfileEntry OBJECT-TYPE
	SYNTAX  LtmConnPoolProfileEntry
	MAX-ACCESS not-accessible
	STATUS current
	DESCRIPTION
		"Columns in the ltmConnPoolProfile Table"
	INDEX {
		ltmConnPoolProfileName
	}
	::= { ltmConnPoolProfileTable 1 }

LtmConnPoolProfileEntry ::=
	SEQUENCE {
        	ltmConnPoolProfileName                                    LongDisplayString,
        	ltmConnPoolProfileConfigSource                            INTEGER,
        	ltmConnPoolProfileDefaultName                             LongDisplayString,
        	ltmConnPoolProfileSrcMaskType                             InetAddressType,
        	ltmConnPoolProfileSrcMask                                 InetAddress,
        	ltmConnPoolProfileMaxSize                                 Gauge,
        	ltmConnPoolProfileMaxAge                                  Gauge,
        	ltmConnPoolProfileMaxReuse                                Gauge,
        	ltmConnPoolProfileIdleTimeout                             Gauge
	}

ltmConnPoolProfileName OBJECT-TYPE
	SYNTAX LongDisplayString
	MAX-ACCESS read-only
	STATUS current
	DESCRIPTION
		"The name of a connection pool profile."
	::= { ltmConnPoolProfileEntry 1 }

ltmConnPoolProfileConfigSource OBJECT-TYPE
	SYNTAX INTEGER {
		usercfg(0),
		basecfg(1)
	}
	MAX-ACCESS read-only
	STATUS current
	DESCRIPTION
		"The state that specifies whether this is a base/pre-configured profile
		or user defined profile."
	::= { ltmConnPoolProfileEntry 2 }

ltmConnPoolProfileDefaultName OBJECT-TYPE
	SYNTAX LongDisplayString
	MAX-ACCESS read-only
	STATUS current
	DESCRIPTION
		"The name of the profile from which the specified profile derives
		its attribute default values."
	::= { ltmConnPoolProfileEntry 3 }

ltmConnPoolProfileSrcMaskType OBJECT-TYPE
	SYNTAX InetAddressType
	MAX-ACCESS read-only
	STATUS current
	DESCRIPTION
		"The IP address type of ltmConnPoolSrcMask"
	::= { ltmConnPoolProfileEntry 4 }

ltmConnPoolProfileSrcMask OBJECT-TYPE
	SYNTAX InetAddress
	MAX-ACCESS read-only
	STATUS current
	DESCRIPTION
		"The mask applied to source address to determine eligibility
		for reuse. It is interpreted within the context of an
		ltmConnPoolSrcMaskType value."
	::= { ltmConnPoolProfileEntry 5 }

ltmConnPoolProfileMaxSize OBJECT-TYPE
	SYNTAX Gauge
	MAX-ACCESS read-only
	STATUS current
	DESCRIPTION
		"The maximum number of connections in pool."
	::= { ltmConnPoolProfileEntry 6 }

ltmConnPoolProfileMaxAge OBJECT-TYPE
	SYNTAX Gauge
	MAX-ACCESS read-only
	STATUS current
	DESCRIPTION
		"The maximum time in seconds to reuse of connections.
		Don't reuse connections older than max_age seconds."
	::= { ltmConnPoolProfileEntry 7 }

ltmConnPoolProfileMaxReuse OBJECT-TYPE
	SYNTAX Gauge
	MAX-ACCESS read-only
	STATUS current
	DESCRIPTION
		"The maximum times to reuse of connections.
		Don't reuse connections older than max_reuse times."
	::= { ltmConnPoolProfileEntry 8 }

ltmConnPoolProfileIdleTimeout OBJECT-TYPE
	SYNTAX Gauge
	MAX-ACCESS read-only
	STATUS current
	DESCRIPTION
		"The idle timeout for connections in the pool."
	::= { ltmConnPoolProfileEntry 9 }

--==================================================================
-- Profile_connpool_stat
--==================================================================
ltmConnPoolProfileStatResetStats OBJECT-TYPE
	SYNTAX INTEGER
	MAX-ACCESS read-write
	STATUS current
	DESCRIPTION
		"The action to reset resettable statistics data in ltmConnPoolProfileStat.
		 Setting this value to 1 will reset statistics data.
		 Note, some statistics data may not be reset including data that are incremental counters."
	::= { ltmConnPoolProfileStat 1 }

ltmConnPoolProfileStatNumber OBJECT-TYPE
	SYNTAX INTEGER
	MAX-ACCESS read-only
	STATUS current
	DESCRIPTION
		"The number of ltmConnPoolProfileStat entries in the table."
	::= { ltmConnPoolProfileStat 2 }

ltmConnPoolProfileStatTable OBJECT-TYPE
	SYNTAX SEQUENCE OF LtmConnPoolProfileStatEntry
	MAX-ACCESS not-accessible
	STATUS current
	DESCRIPTION
		"A table containing statistic information of connection pool profiles."
	::= { ltmConnPoolProfileStat 3 }

ltmConnPoolProfileStatEntry OBJECT-TYPE
	SYNTAX  LtmConnPoolProfileStatEntry
	MAX-ACCESS not-accessible
	STATUS current
	DESCRIPTION
		"Columns in the ltmConnPoolProfileStat Table"
	INDEX {
		ltmConnPoolProfileStatName
	}
	::= { ltmConnPoolProfileStatTable 1 }

LtmConnPoolProfileStatEntry ::=
	SEQUENCE {
        	ltmConnPoolProfileStatName                                LongDisplayString,
        	ltmConnPoolProfileStatCurSize                             Gauge,
        	ltmConnPoolProfileStatMaxSize                             Gauge,
        	ltmConnPoolProfileStatReuses                              Gauge,
        	ltmConnPoolProfileStatConnects                            Gauge
	}

ltmConnPoolProfileStatName OBJECT-TYPE
	SYNTAX LongDisplayString
	MAX-ACCESS read-only
	STATUS current
	DESCRIPTION
		"The name of a connection pool profile."
	::= { ltmConnPoolProfileStatEntry 1 }

ltmConnPoolProfileStatCurSize OBJECT-TYPE
	SYNTAX Gauge
	MAX-ACCESS read-only
	STATUS current
	DESCRIPTION
		"The number of currently idle connections in the pool."
	::= { ltmConnPoolProfileStatEntry 2 }

ltmConnPoolProfileStatMaxSize OBJECT-TYPE
	SYNTAX Gauge
	MAX-ACCESS read-only
	STATUS current
	DESCRIPTION
		"The number of idle connections in the pool."
	::= { ltmConnPoolProfileStatEntry 3 }

ltmConnPoolProfileStatReuses OBJECT-TYPE
	SYNTAX Gauge
	MAX-ACCESS read-only
	STATUS current
	DESCRIPTION
		"The number of times a connection was reused from the pool."
	::= { ltmConnPoolProfileStatEntry 4 }

ltmConnPoolProfileStatConnects OBJECT-TYPE
	SYNTAX Gauge
	MAX-ACCESS read-only
	STATUS current
	DESCRIPTION
		"The number of times a new connection was initiated."
	::= { ltmConnPoolProfileStatEntry 5 }

--==================================================================
-- Profile_bigproto
--==================================================================
ltmFastL4ProfileNumber OBJECT-TYPE
	SYNTAX INTEGER
	MAX-ACCESS read-only
	STATUS current
	DESCRIPTION
		"The number of ltmFastL4Profile entries in the table."
	::= { ltmFastL4Profile 1 }

ltmFastL4ProfileTable OBJECT-TYPE
	SYNTAX SEQUENCE OF LtmFastL4ProfileEntry
	MAX-ACCESS not-accessible
	STATUS current
	DESCRIPTION
		"A table containing information of fast L4  profiles."
	::= { ltmFastL4Profile 2 }

ltmFastL4ProfileEntry OBJECT-TYPE
	SYNTAX  LtmFastL4ProfileEntry
	MAX-ACCESS not-accessible
	STATUS current
	DESCRIPTION
		"Columns in the ltmFastL4Profile Table"
	INDEX {
		ltmFastL4ProfileName
	}
	::= { ltmFastL4ProfileTable 1 }

LtmFastL4ProfileEntry ::=
	SEQUENCE {
        	ltmFastL4ProfileName                                      LongDisplayString,
        	ltmFastL4ProfileConfigSource                              INTEGER,
        	ltmFastL4ProfileDefaultName                               LongDisplayString,
        	ltmFastL4ProfileResetOnTimeout                            INTEGER,
        	ltmFastL4ProfileIpFragReass                               INTEGER,
        	ltmFastL4ProfileIdleTimeout                               Gauge,
        	ltmFastL4ProfileTcpHandshakeTimeout                       Gauge,
        	ltmFastL4ProfileMssOverride                               Gauge,
        	ltmFastL4ProfilePvaAccelMode                              INTEGER,
        	ltmFastL4ProfileTcpTimestampMode                          INTEGER,
        	ltmFastL4ProfileTcpWscaleMode                             INTEGER,
        	ltmFastL4ProfileTcpGenerateIsn                            INTEGER,
        	ltmFastL4ProfileTcpStripSack                              INTEGER,
        	ltmFastL4ProfileIpTosToClient                             INTEGER,
        	ltmFastL4ProfileIpTosToServer                             INTEGER,
        	ltmFastL4ProfileLinkQosToClient                           INTEGER,
        	ltmFastL4ProfileLinkQosToServer                           INTEGER,
        	ltmFastL4ProfileRttFromClient                             INTEGER,
        	ltmFastL4ProfileRttFromServer                             INTEGER,
        	ltmFastL4ProfileTcpCloseTimeout                           Gauge,
        	ltmFastL4ProfileLooseInitiation                           INTEGER,
        	ltmFastL4ProfileLooseClose                                INTEGER,
        	ltmFastL4ProfileHardSyncookie                             INTEGER,
        	ltmFastL4ProfileSoftSyncookie                             INTEGER,
        	ltmFastL4ProfileLateBinding                               INTEGER,
        	ltmFastL4ProfileExplicitFlowMigration                     INTEGER,
        	ltmFastL4ProfileClientTimeout                             Gauge,
        	ltmFastL4ProfileTimeoutRecovery                           INTEGER
	}

ltmFastL4ProfileName OBJECT-TYPE
	SYNTAX LongDisplayString
	MAX-ACCESS read-only
	STATUS current
	DESCRIPTION
		"The name of a fast L4 profile."
	::= { ltmFastL4ProfileEntry 1 }

ltmFastL4ProfileConfigSource OBJECT-TYPE
	SYNTAX INTEGER {
		usercfg(0),
		basecfg(1)
	}
	MAX-ACCESS read-only
	STATUS current
	DESCRIPTION
		"The state that specifies whether this is a base/pre-configured profile
		or user defined profile."
	::= { ltmFastL4ProfileEntry 2 }

ltmFastL4ProfileDefaultName OBJECT-TYPE
	SYNTAX LongDisplayString
	MAX-ACCESS read-only
	STATUS current
	DESCRIPTION
		"The name of the profile from which the specified profile derives
		its attribute default values."
	::= { ltmFastL4ProfileEntry 3 }

ltmFastL4ProfileResetOnTimeout OBJECT-TYPE
	SYNTAX INTEGER {
		false(0),
		true(1)
	}
	MAX-ACCESS read-only
	STATUS current
	DESCRIPTION
		"The feature of reset for idle timeout.
		If true and a TCP connection exceeds its idle_timeout, send a reset
		in addition to deleting the connection."
	::= { ltmFastL4ProfileEntry 4 }

ltmFastL4ProfileIpFragReass OBJECT-TYPE
	SYNTAX INTEGER {
		false(0),
		true(1)
	}
	MAX-ACCESS read-only
	STATUS current
	DESCRIPTION
		"The feature for reassembling IP fragments. If true, reassemble IP fragments."
	::= { ltmFastL4ProfileEntry 5 }

ltmFastL4ProfileIdleTimeout OBJECT-TYPE
	SYNTAX Gauge
	MAX-ACCESS read-only
	STATUS current
	DESCRIPTION
		"The number of seconds without traffic before a connection is eligible
		for deletion."
	::= { ltmFastL4ProfileEntry 6 }

ltmFastL4ProfileTcpHandshakeTimeout OBJECT-TYPE
	SYNTAX Gauge
	MAX-ACCESS read-only
	STATUS current
	DESCRIPTION
		"The number of seconds without traffic before a connection in the SYN
		received state is eligible for deletion.
		If set to 0, ltmFastL4ProfileIdleTimeout will be used."
	::= { ltmFastL4ProfileEntry 7 }

ltmFastL4ProfileMssOverride OBJECT-TYPE
	SYNTAX Gauge
	MAX-ACCESS read-only
	STATUS current
	DESCRIPTION
		"If non-zero and less than the 1460 default, this value overrides
		the maximum segment size"
	::= { ltmFastL4ProfileEntry 8 }

ltmFastL4ProfilePvaAccelMode OBJECT-TYPE
	SYNTAX INTEGER {
		full(0),
		partial(1),
		none(2)
	}
	MAX-ACCESS read-only
	STATUS current
	DESCRIPTION
		"The preferred Packet Velocity ASIC (PVA) acceleration mode."
	::= { ltmFastL4ProfileEntry 9 }

ltmFastL4ProfileTcpTimestampMode OBJECT-TYPE
	SYNTAX INTEGER {
		preserve(0),
		strip(1),
		rewrite(2)
	}
	MAX-ACCESS read-only
	STATUS current
	DESCRIPTION
		"The option to preserver, strip or rewrite TCP timestamps."
	::= { ltmFastL4ProfileEntry 10 }

ltmFastL4ProfileTcpWscaleMode OBJECT-TYPE
	SYNTAX INTEGER {
		preserve(0),
		strip(1),
		rewrite(2)
	}
	MAX-ACCESS read-only
	STATUS current
	DESCRIPTION
		"The option to preserver or strip window scale option."
	::= { ltmFastL4ProfileEntry 11 }

ltmFastL4ProfileTcpGenerateIsn OBJECT-TYPE
	SYNTAX INTEGER {
		false(0),
		true(1)
	}
	MAX-ACCESS read-only
	STATUS current
	DESCRIPTION
		"The option to generate own sequence numbers on all SYNs conformant
		with RFC1948, and hence allowing timestamp recycling."
	::= { ltmFastL4ProfileEntry 12 }

ltmFastL4ProfileTcpStripSack OBJECT-TYPE
	SYNTAX INTEGER {
		false(0),
		true(1)
	}
	MAX-ACCESS read-only
	STATUS current
	DESCRIPTION
		"The option to block TCP SackOK option from passing to server
		on an initiating SYN."
	::= { ltmFastL4ProfileEntry 13 }

ltmFastL4ProfileIpTosToClient OBJECT-TYPE
	SYNTAX INTEGER
	MAX-ACCESS read-only
	STATUS current
	DESCRIPTION
		"The IP type of service set in packets sent to the client-side."
	::= { ltmFastL4ProfileEntry 14 }

ltmFastL4ProfileIpTosToServer OBJECT-TYPE
	SYNTAX INTEGER
	MAX-ACCESS read-only
	STATUS current
	DESCRIPTION
		"The IP type of service set in packets sent to the server-side."
	::= { ltmFastL4ProfileEntry 15 }

ltmFastL4ProfileLinkQosToClient OBJECT-TYPE
	SYNTAX INTEGER
	MAX-ACCESS read-only
	STATUS current
	DESCRIPTION
		"The link quality of service set in packets sent to the client-side."
	::= { ltmFastL4ProfileEntry 16 }

ltmFastL4ProfileLinkQosToServer OBJECT-TYPE
	SYNTAX INTEGER
	MAX-ACCESS read-only
	STATUS current
	DESCRIPTION
		"The link quality of service set in packets sent to the server-side."
	::= { ltmFastL4ProfileEntry 17 }

ltmFastL4ProfileRttFromClient OBJECT-TYPE
	SYNTAX INTEGER {
		false(0),
		true(1)
	}
	MAX-ACCESS read-only
	STATUS current
	DESCRIPTION
		"The option to use TCP timestamp options to measure the round trip
		time to the client."
	::= { ltmFastL4ProfileEntry 18 }

ltmFastL4ProfileRttFromServer OBJECT-TYPE
	SYNTAX INTEGER {
		false(0),
		true(1)
	}
	MAX-ACCESS read-only
	STATUS current
	DESCRIPTION
		"The option to use TCP timestamp options to measure the round trip
		time to the server."
	::= { ltmFastL4ProfileEntry 19 }

ltmFastL4ProfileTcpCloseTimeout OBJECT-TYPE
	SYNTAX Gauge
	MAX-ACCESS read-only
	STATUS current
	DESCRIPTION
		"The number of seconds without traffic before a connection in the FIN
		received state is eligible for deletion.
		This is only used when ltmFastL4ProfileLooseInitiation or
		ltmFastL4ProfileLooseClose is enabled."
	::= { ltmFastL4ProfileEntry 20 }

ltmFastL4ProfileLooseInitiation OBJECT-TYPE
	SYNTAX INTEGER {
		false(0),
		true(1)
	}
	MAX-ACCESS read-only
	STATUS current
	DESCRIPTION
		"The option to allow any TCP packet to initiate a connection (rather
		than requiring a SYN."
	::= { ltmFastL4ProfileEntry 21 }

ltmFastL4ProfileLooseClose OBJECT-TYPE
	SYNTAX INTEGER {
		false(0),
		true(1)
	}
	MAX-ACCESS read-only
	STATUS current
	DESCRIPTION
		"The option to aggressively close out a connection by allowing TMM to switch
		the ltmFastL4ProfileIdleTimeout to ltmFastL4ProfileTcpCloseTimeout
		once the first FIN packet has been seen."
	::= { ltmFastL4ProfileEntry 22 }

ltmFastL4ProfileHardSyncookie OBJECT-TYPE
	SYNTAX INTEGER {
		false(0),
		true(1)
	}
	MAX-ACCESS read-only
	STATUS current
	DESCRIPTION
		"The option to enable hardware SYN cookie protection using Packet Velocity ASIC (PVA)."
	::= { ltmFastL4ProfileEntry 23 }

ltmFastL4ProfileSoftSyncookie OBJECT-TYPE
	SYNTAX INTEGER {
		false(0),
		true(1)
	}
	MAX-ACCESS read-only
	STATUS current
	DESCRIPTION
		"The state indicating whether or not software SYN cookie protection is enable."
	::= { ltmFastL4ProfileEntry 24 }

ltmFastL4ProfileLateBinding OBJECT-TYPE
	SYNTAX INTEGER {
		false(0),
		true(1)
	}
	MAX-ACCESS read-only
	STATUS current
	DESCRIPTION
		"The state indicating whether or not Late Binding is enabled."
	::= { ltmFastL4ProfileEntry 25 }

ltmFastL4ProfileExplicitFlowMigration OBJECT-TYPE
	SYNTAX INTEGER {
		false(0),
		true(1)
	}
	MAX-ACCESS read-only
	STATUS current
	DESCRIPTION
		"The state indicating whether connections are automatically migrated
	        into the hardware (false) or whether they must be explicitly migrated
	        to hardware by the iRule command BIGTCP::release_flow (true)."
	::= { ltmFastL4ProfileEntry 26 }

ltmFastL4ProfileClientTimeout OBJECT-TYPE
	SYNTAX Gauge
	MAX-ACCESS read-only
	STATUS current
	DESCRIPTION
		"The number of seconds allowed for a client to transmit enough data to select
	        a server when late binding is enabled."
	::= { ltmFastL4ProfileEntry 27 }

ltmFastL4ProfileTimeoutRecovery OBJECT-TYPE
	SYNTAX INTEGER {
		disconnect(0),
		fallback(1)
	}
	MAX-ACCESS read-only
	STATUS current
	DESCRIPTION
		"The action to take when late binding timeout occurs on a connection."
	::= { ltmFastL4ProfileEntry 28 }

--==================================================================
-- Profile_ftp
--==================================================================
ltmFtpProfileNumber OBJECT-TYPE
	SYNTAX INTEGER
	MAX-ACCESS read-only
	STATUS current
	DESCRIPTION
		"The number of ltmFtpProfile entries in the table."
	::= { ltmFtpProfile 1 }

ltmFtpProfileTable OBJECT-TYPE
	SYNTAX SEQUENCE OF LtmFtpProfileEntry
	MAX-ACCESS not-accessible
	STATUS current
	DESCRIPTION
		"A table containing information of FTP profiles."
	::= { ltmFtpProfile 2 }

ltmFtpProfileEntry OBJECT-TYPE
	SYNTAX  LtmFtpProfileEntry
	MAX-ACCESS not-accessible
	STATUS current
	DESCRIPTION
		"Columns in the ltmFtpProfile Table"
	INDEX {
		ltmFtpProfileName
	}
	::= { ltmFtpProfileTable 1 }

LtmFtpProfileEntry ::=
	SEQUENCE {
        	ltmFtpProfileName                                         LongDisplayString,
        	ltmFtpProfileConfigSource                                 INTEGER,
        	ltmFtpProfileDefaultName                                  LongDisplayString,
        	ltmFtpProfileTranslateExtended                            INTEGER,
        	ltmFtpProfileDataPort                                     InetPortNumber,
        	ltmFtpProfileLogPublisher                                 LongDisplayString,
        	ltmFtpProfileLogProfile                                   LongDisplayString
	}

ltmFtpProfileName OBJECT-TYPE
	SYNTAX LongDisplayString
	MAX-ACCESS read-only
	STATUS current
	DESCRIPTION
		"The name of a FTP profile."
	::= { ltmFtpProfileEntry 1 }

ltmFtpProfileConfigSource OBJECT-TYPE
	SYNTAX INTEGER {
		usercfg(0),
		basecfg(1)
	}
	MAX-ACCESS read-only
	STATUS current
	DESCRIPTION
		"The state that specifies whether this is a base/pre-configured profile
		or user defined profile."
	::= { ltmFtpProfileEntry 2 }

ltmFtpProfileDefaultName OBJECT-TYPE
	SYNTAX LongDisplayString
	MAX-ACCESS read-only
	STATUS current
	DESCRIPTION
		"The name of the profile from which the specified profile derives
		its attribute default values."
	::= { ltmFtpProfileEntry 3 }

ltmFtpProfileTranslateExtended OBJECT-TYPE
	SYNTAX INTEGER {
		false(0),
		true(1)
	}
	MAX-ACCESS read-only
	STATUS current
	DESCRIPTION
		"Whether or not automatically translated RFC2428 extended requests
		EPSV and EPRT to PASV and PORT when talking to IPv4 servers."
	::= { ltmFtpProfileEntry 4 }

ltmFtpProfileDataPort OBJECT-TYPE
	SYNTAX InetPortNumber
	MAX-ACCESS read-only
	STATUS current
	DESCRIPTION
		"The data channel port used for this FTP profile. By default,
		this is 20, but may need to be changed for non-default port FTP."
	::= { ltmFtpProfileEntry 5 }

ltmFtpProfileLogPublisher OBJECT-TYPE
	SYNTAX LongDisplayString
	MAX-ACCESS read-only
	STATUS current
	DESCRIPTION
		"Specifies the name of the log publisher that logs ALG events, if any."
	::= { ltmFtpProfileEntry 6 }

ltmFtpProfileLogProfile OBJECT-TYPE
	SYNTAX LongDisplayString
	MAX-ACCESS read-only
	STATUS current
	DESCRIPTION
		"Specifies the name of the log profile that control the logging of ALG events, if any."
	::= { ltmFtpProfileEntry 7 }

--==================================================================
-- Profile_http
--==================================================================
ltmHttpProfileNumber OBJECT-TYPE
	SYNTAX INTEGER
	MAX-ACCESS read-only
	STATUS current
	DESCRIPTION
		"The number of ltmHttpProfile entries in the table."
	::= { ltmHttpProfile 1 }

ltmHttpProfileTable OBJECT-TYPE
	SYNTAX SEQUENCE OF LtmHttpProfileEntry
	MAX-ACCESS not-accessible
	STATUS current
	DESCRIPTION
		"A table containing information of HTTP profiles."
	::= { ltmHttpProfile 2 }

ltmHttpProfileEntry OBJECT-TYPE
	SYNTAX  LtmHttpProfileEntry
	MAX-ACCESS not-accessible
	STATUS current
	DESCRIPTION
		"Columns in the ltmHttpProfile Table"
	INDEX {
		ltmHttpProfileName
	}
	::= { ltmHttpProfileTable 1 }

LtmHttpProfileEntry ::=
	SEQUENCE {
        	ltmHttpProfileName                                        LongDisplayString,
        	ltmHttpProfileConfigSource                                INTEGER,
        	ltmHttpProfileDefaultName                                 LongDisplayString,
        	ltmHttpProfileBasicAuthRealm                              LongDisplayString,
        	ltmHttpProfileOneConnect                                  INTEGER,
        	ltmHttpProfileHeaderInsert                                LongDisplayString,
        	ltmHttpProfileHeaderErase                                 LongDisplayString,
        	ltmHttpProfileFallbackHost                                LongDisplayString,
        	ltmHttpProfileCompressMode                                INTEGER,
        	ltmHttpProfileCompressMinSize                             Gauge,
        	ltmHttpProfileCompressBufferSize                          Gauge,
        	ltmHttpProfileCompressVaryHeader                          INTEGER,
        	ltmHttpProfileCompressAllowHttp10                         INTEGER,
        	ltmHttpProfileCompressGzipMemlevel                        Gauge,
        	ltmHttpProfileCompressGzipWindowsize                      Gauge,
        	ltmHttpProfileCompressGzipLevel                           Gauge,
        	ltmHttpProfileCompressKeepAcceptEncoding                  INTEGER,
        	ltmHttpProfileCompressBrowserWorkarounds                  INTEGER,
        	ltmHttpProfileRequestChunking                             INTEGER,
        	ltmHttpProfileResponseChunking                            INTEGER,
        	ltmHttpProfileLwsMaxColumn                                Gauge,
        	ltmHttpProfileLwsSeparator                                LongDisplayString,
        	ltmHttpProfileRedirectRewrite                             INTEGER,
        	ltmHttpProfileMaxHeaderSize                               Gauge,
        	ltmHttpProfilePipelining                                  INTEGER,
        	ltmHttpProfileInsertXforwardedFor                         INTEGER,
        	ltmHttpProfileMaxRequests                                 Gauge,
        	ltmHttpProfileCompressCpusaver                            INTEGER,
        	ltmHttpProfileCompressCpusaverHigh                        Gauge,
        	ltmHttpProfileCompressCpusaverLow                         Gauge,
        	ltmHttpProfileRamcache                                    INTEGER,
        	ltmHttpProfileRamcacheSize                                Gauge,
        	ltmHttpProfileRamcacheMaxEntries                          Gauge,
        	ltmHttpProfileRamcacheMaxAge                              Gauge,
        	ltmHttpProfileRamcacheObjectMinSize                       Gauge,
        	ltmHttpProfileRamcacheObjectMaxSize                       Gauge,
        	ltmHttpProfileRamcacheIgnoreClient                        INTEGER,
        	ltmHttpProfileRamcacheAgingRate                           Gauge,
        	ltmHttpProfileRamcacheInsertAgeHeader                     INTEGER,
        	ltmHttpProfileCompressPreferredMethod                     INTEGER,
        	ltmHttpProfileServerAgentName                             LongDisplayString,
        	ltmHttpProfilePassthroughPipeline                         INTEGER,
        	ltmHttpProfileTruncatedRedirects                          INTEGER,
        	ltmHttpProfilePassthroughOversizeClientHeaders            INTEGER,
        	ltmHttpProfilePassthroughOversizeServerHeaders            INTEGER,
        	ltmHttpProfilePassthroughExcessClientHeaders              INTEGER,
        	ltmHttpProfilePassthroughExcessServerHeaders              INTEGER,
        	ltmHttpProfilePassthroughUnknownMethod                    INTEGER,
        	ltmHttpProfileHstsMode                                    INTEGER,
        	ltmHttpProfileHstsMaximumAge                              Gauge,
        	ltmHttpProfileHstsIncludeSubdomains                       INTEGER,
        	ltmHttpProfileHstsPreload                                 INTEGER,
        	ltmHttpProfileOneConnectStatusReuse                       LongDisplayString
	}

ltmHttpProfileName OBJECT-TYPE
	SYNTAX LongDisplayString
	MAX-ACCESS read-only
	STATUS current
	DESCRIPTION
		"The name of a HTTP profile."
	::= { ltmHttpProfileEntry 1 }

ltmHttpProfileConfigSource OBJECT-TYPE
	SYNTAX INTEGER {
		usercfg(0),
		basecfg(1)
	}
	MAX-ACCESS read-only
	STATUS current
	DESCRIPTION
		"The state that specifies whether this is a base/pre-configured profile
		or user defined profile."
	::= { ltmHttpProfileEntry 2 }

ltmHttpProfileDefaultName OBJECT-TYPE
	SYNTAX LongDisplayString
	MAX-ACCESS read-only
	STATUS current
	DESCRIPTION
		"The name of the profile from which the specified profile derives
		its attribute default values."
	::= { ltmHttpProfileEntry 3 }

ltmHttpProfileBasicAuthRealm OBJECT-TYPE
	SYNTAX LongDisplayString
	MAX-ACCESS read-only
	STATUS current
	DESCRIPTION
		"The basic authentication realm of the specified HTTP profile."
	::= { ltmHttpProfileEntry 4 }

ltmHttpProfileOneConnect OBJECT-TYPE
	SYNTAX INTEGER {
		false(0),
		true(1)
	}
	MAX-ACCESS read-only
	STATUS current
	DESCRIPTION
		"The state that specifies whether OneConnect HTTP header
		transformation is used for the specified HTTP profile."
	::= { ltmHttpProfileEntry 5 }

ltmHttpProfileHeaderInsert OBJECT-TYPE
	SYNTAX LongDisplayString
	MAX-ACCESS read-only
	STATUS current
	DESCRIPTION
		"The header to be inserted into the HTTP header for
		the specified HTTP profile."
	::= { ltmHttpProfileEntry 6 }

ltmHttpProfileHeaderErase OBJECT-TYPE
	SYNTAX LongDisplayString
	MAX-ACCESS read-only
	STATUS current
	DESCRIPTION
		"The header to be erased into the HTTP header for
		the specified HTTP profile."
	::= { ltmHttpProfileEntry 7 }

ltmHttpProfileFallbackHost OBJECT-TYPE
	SYNTAX LongDisplayString
	MAX-ACCESS read-only
	STATUS current
	DESCRIPTION
		"The fallback host name used in HTTP redirect for
		the specified HTTP profile."
	::= { ltmHttpProfileEntry 8 }

ltmHttpProfileCompressMode OBJECT-TYPE
	SYNTAX INTEGER {
		disable(0),
		enable(1),
		selective(2)
	}
	MAX-ACCESS read-only
	STATUS	 deprecated
	DESCRIPTION
		"Deprecated!  The state that specifies whether compression is enabled."
	::= { ltmHttpProfileEntry 9 }

ltmHttpProfileCompressMinSize OBJECT-TYPE
	SYNTAX Gauge
	MAX-ACCESS read-only
	STATUS	 deprecated
	DESCRIPTION
		"Deprecated!  The value that specifies the minimum length of the server
		responses (in bytes) to be considered acceptable for compression."
	::= { ltmHttpProfileEntry 10 }

ltmHttpProfileCompressBufferSize OBJECT-TYPE
	SYNTAX Gauge
	MAX-ACCESS read-only
	STATUS	 deprecated
	DESCRIPTION
		"Deprecated!  The value that specifies the maximum number of uncompressed bytes
		that the compression proxy will buffer before it decides whether or
		not to compress the server's response, in case the server's response
		headers don't specify the content length of the response."
	::= { ltmHttpProfileEntry 11 }

ltmHttpProfileCompressVaryHeader OBJECT-TYPE
	SYNTAX INTEGER {
		false(0),
		true(1)
	}
	MAX-ACCESS read-only
	STATUS	 deprecated
	DESCRIPTION
		"Deprecated!  The state that specifies whether to insert the header
		'Vary: Accept-Encoding' in the server response for responses that
		have been compressed. If the 'Vary:' header already exists in the
		server response, then the value 'Accept-Encoding' will be appended to it."
	::= { ltmHttpProfileEntry 12 }

ltmHttpProfileCompressAllowHttp10 OBJECT-TYPE
	SYNTAX INTEGER {
		false(0),
		true(1)
	}
	MAX-ACCESS read-only
	STATUS	 deprecated
	DESCRIPTION
		"Deprecated!  The state that specifies whether to allow compression on responses
		to HTTP 1.0 requests."
	::= { ltmHttpProfileEntry 13 }

ltmHttpProfileCompressGzipMemlevel OBJECT-TYPE
	SYNTAX Gauge
	MAX-ACCESS read-only
	STATUS	 deprecated
	DESCRIPTION
		"Deprecated!  The amount of memory that the proxy will use when doing compression.
		It must be an integer no less than 1 and no greater than 9. Higher
		values produce faster compression at the expense of more memory usage.
		The default memory level will be 8."
	::= { ltmHttpProfileEntry 14 }

ltmHttpProfileCompressGzipWindowsize OBJECT-TYPE
	SYNTAX Gauge
	MAX-ACCESS read-only
	STATUS	 deprecated
	DESCRIPTION
		"Deprecated!  The number of bits in the window size that the compression proxy
		will use when compressing the server response. It should be an integer
		no less than 8 and no greater than 15. Higher values produce better
		compression ratios at the expense of more memory usage.
		The default window size will be 15."
	::= { ltmHttpProfileEntry 15 }

ltmHttpProfileCompressGzipLevel OBJECT-TYPE
	SYNTAX Gauge
	MAX-ACCESS read-only
	STATUS	 deprecated
	DESCRIPTION
		"Deprecated!  The speed of compression that is applied to the response. Minimum
		value is 1, maximum is 9. The lower numbers give faster compression
		with lower ratios, and higher numbers give slower compression with
		higher ratios."
	::= { ltmHttpProfileEntry 16 }

ltmHttpProfileCompressKeepAcceptEncoding OBJECT-TYPE
	SYNTAX INTEGER {
		false(0),
		true(1)
	}
	MAX-ACCESS read-only
	STATUS	 deprecated
	DESCRIPTION
		"Deprecated!  The state of the option to keep client-encoding header."
	::= { ltmHttpProfileEntry 17 }

ltmHttpProfileCompressBrowserWorkarounds OBJECT-TYPE
	SYNTAX INTEGER {
		false(0),
		true(1)
	}
	MAX-ACCESS read-only
	STATUS	 deprecated
	DESCRIPTION
		"Deprecated!  The option to control whether or not to disable compression for
		known browsers that cannot handle certain types of compressed
		responses properly. If it's true, compression for known browsers
		will be disabled."
	::= { ltmHttpProfileEntry 18 }

ltmHttpProfileRequestChunking OBJECT-TYPE
	SYNTAX INTEGER {
		preserve(0),
		selective(1),
		rechunk(3),
		sustain(4)
	}
	MAX-ACCESS read-only
	STATUS current
	DESCRIPTION
		"The HTTP chunk mode for the requests."
	::= { ltmHttpProfileEntry 19 }

ltmHttpProfileResponseChunking OBJECT-TYPE
	SYNTAX INTEGER {
		preserve(0),
		selective(1),
		unchunk(2),
		rechunk(3),
		sustain(4)
	}
	MAX-ACCESS read-only
	STATUS current
	DESCRIPTION
		"The HTTP chunk mode for the responses."
	::= { ltmHttpProfileEntry 20 }

ltmHttpProfileLwsMaxColumn OBJECT-TYPE
	SYNTAX Gauge
	MAX-ACCESS read-only
	STATUS current
	DESCRIPTION
		"The linear white space maximum column sizes used to support
		multi-line header insertion."
	::= { ltmHttpProfileEntry 21 }

ltmHttpProfileLwsSeparator OBJECT-TYPE
	SYNTAX LongDisplayString
	MAX-ACCESS read-only
	STATUS current
	DESCRIPTION
		"The linear white space separator strings for the specified HTTP profile."
	::= { ltmHttpProfileEntry 22 }

ltmHttpProfileRedirectRewrite OBJECT-TYPE
	SYNTAX INTEGER {
		none(0),
		all(1),
		matching(2),
		nodes(3)
	}
	MAX-ACCESS read-only
	STATUS current
	DESCRIPTION
		"The HTTP redirect/rewrite mode for the responses."
	::= { ltmHttpProfileEntry 23 }

ltmHttpProfileMaxHeaderSize OBJECT-TYPE
	SYNTAX Gauge
	MAX-ACCESS read-only
	STATUS current
	DESCRIPTION
		"The maximum size of the headers."
	::= { ltmHttpProfileEntry 24 }

ltmHttpProfilePipelining OBJECT-TYPE
	SYNTAX INTEGER {
		disabled(0),
		enabled(1)
	}
	MAX-ACCESS read-only
	STATUS	 deprecated
	DESCRIPTION
		"Deprecated!  The state indicating whether pipelining is enabled for this profile."
	::= { ltmHttpProfileEntry 25 }

ltmHttpProfileInsertXforwardedFor OBJECT-TYPE
	SYNTAX INTEGER {
		disabled(0),
		enabled(1)
	}
	MAX-ACCESS read-only
	STATUS current
	DESCRIPTION
		"The state indicating whether inserting X-Forwarded-For
		is enabled for this profile."
	::= { ltmHttpProfileEntry 26 }

ltmHttpProfileMaxRequests OBJECT-TYPE
	SYNTAX Gauge
	MAX-ACCESS read-only
	STATUS current
	DESCRIPTION
		"The maximum connection requests allowed. The connection will be
		forced closed when this limit is reached."
	::= { ltmHttpProfileEntry 27 }

ltmHttpProfileCompressCpusaver OBJECT-TYPE
	SYNTAX INTEGER {
		false(0),
		true(1)
	}
	MAX-ACCESS read-only
	STATUS	 deprecated
	DESCRIPTION
		"Deprecated!  The state indicating whether CPU saving mode is enable or not
		when doing compression."
	::= { ltmHttpProfileEntry 28 }

ltmHttpProfileCompressCpusaverHigh OBJECT-TYPE
	SYNTAX Gauge
	MAX-ACCESS read-only
	STATUS	 deprecated
	DESCRIPTION
		"Deprecated!  The CPU saver high threshold. When CPU utilization exceeds this value,
		compression is switched to NULL compression."
	::= { ltmHttpProfileEntry 29 }

ltmHttpProfileCompressCpusaverLow OBJECT-TYPE
	SYNTAX Gauge
	MAX-ACCESS read-only
	STATUS	 deprecated
	DESCRIPTION
		"Deprecated!  The CPU saver low threshold. When CPU utilization drops below
		this value, compression is switched to full throttle."
	::= { ltmHttpProfileEntry 30 }

ltmHttpProfileRamcache OBJECT-TYPE
	SYNTAX INTEGER {
		disable(0),
		enable(1)
	}
	MAX-ACCESS read-only
	STATUS	 deprecated
	DESCRIPTION
		"Deprecated!  The state the whether RAM cache is enabled or not."
	::= { ltmHttpProfileEntry 31 }

ltmHttpProfileRamcacheSize OBJECT-TYPE
	SYNTAX Gauge
	MAX-ACCESS read-only
	STATUS	 deprecated
	DESCRIPTION
		"Deprecated!  The maximum cache size in MB's."
	::= { ltmHttpProfileEntry 32 }

ltmHttpProfileRamcacheMaxEntries OBJECT-TYPE
	SYNTAX Gauge
	MAX-ACCESS read-only
	STATUS	 deprecated
	DESCRIPTION
		"Deprecated!  The maximum cache entries."
	::= { ltmHttpProfileEntry 33 }

ltmHttpProfileRamcacheMaxAge OBJECT-TYPE
	SYNTAX Gauge
	MAX-ACCESS read-only
	STATUS	 deprecated
	DESCRIPTION
		"Deprecated!  The maximum age of cached object."
	::= { ltmHttpProfileEntry 34 }

ltmHttpProfileRamcacheObjectMinSize OBJECT-TYPE
	SYNTAX Gauge
	MAX-ACCESS read-only
	STATUS	 deprecated
	DESCRIPTION
		"Deprecated!  The minimum size requirement for cached object in bytes."
	::= { ltmHttpProfileEntry 35 }

ltmHttpProfileRamcacheObjectMaxSize OBJECT-TYPE
	SYNTAX Gauge
	MAX-ACCESS read-only
	STATUS	 deprecated
	DESCRIPTION
		"Deprecated!  The maximum size limitation for cached object in bytes."
	::= { ltmHttpProfileEntry 36 }

ltmHttpProfileRamcacheIgnoreClient OBJECT-TYPE
	SYNTAX INTEGER {
		none(0),
		maxage(1),
		all(2)
	}
	MAX-ACCESS read-only
	STATUS	 deprecated
	DESCRIPTION
		"Deprecated!  The state that Ram cache ignores client cache."
	::= { ltmHttpProfileEntry 37 }

ltmHttpProfileRamcacheAgingRate OBJECT-TYPE
	SYNTAX Gauge
	MAX-ACCESS read-only
	STATUS	 deprecated
	DESCRIPTION
		"Deprecated!  The aging rate for the RAM cache."
	::= { ltmHttpProfileEntry 38 }

ltmHttpProfileRamcacheInsertAgeHeader OBJECT-TYPE
	SYNTAX INTEGER {
		disable(0),
		enable(1)
	}
	MAX-ACCESS read-only
	STATUS	 deprecated
	DESCRIPTION
		"Deprecated!  The mode that indicates whether to insert the Age headers for RAM cache."
	::= { ltmHttpProfileEntry 39 }

ltmHttpProfileCompressPreferredMethod OBJECT-TYPE
	SYNTAX INTEGER {
		deflate(0),
		gzip(1)
	}
	MAX-ACCESS read-only
	STATUS	 deprecated
	DESCRIPTION
		"Deprecated!  The option for preferred compression method."
	::= { ltmHttpProfileEntry 40 }

ltmHttpProfileServerAgentName OBJECT-TYPE
	SYNTAX LongDisplayString
	MAX-ACCESS read-only
	STATUS current
	DESCRIPTION
		"The server header sent in responses that the BIG-IP itself
		 generates. The default value is BigIP. If is no string is set
	         as the value, then no server header will be added to such responses."
	::= { ltmHttpProfileEntry 41 }

ltmHttpProfilePassthroughPipeline OBJECT-TYPE
	SYNTAX INTEGER {
		reject(0),
		allow(1),
		passthrough(2)
	}
	MAX-ACCESS read-only
	STATUS current
	DESCRIPTION
		"The state indicating behavior on seeing pipelined data in this profile."
	::= { ltmHttpProfileEntry 42 }

ltmHttpProfileTruncatedRedirects OBJECT-TYPE
	SYNTAX INTEGER {
		disabled(0),
		enabled(1)
	}
	MAX-ACCESS read-only
	STATUS current
	DESCRIPTION
		"The state indicating behavior on seeing a truncated redirect in this profile."
	::= { ltmHttpProfileEntry 43 }

ltmHttpProfilePassthroughOversizeClientHeaders OBJECT-TYPE
	SYNTAX INTEGER {
		false(0),
		true(1)
	}
	MAX-ACCESS read-only
	STATUS current
	DESCRIPTION
		"The state indicating passthrough behavior on seeing oversize client headers in this profile."
	::= { ltmHttpProfileEntry 44 }

ltmHttpProfilePassthroughOversizeServerHeaders OBJECT-TYPE
	SYNTAX INTEGER {
		false(0),
		true(1)
	}
	MAX-ACCESS read-only
	STATUS current
	DESCRIPTION
		"The state indicating passthrough behavior on seeing oversize server headers in this profile."
	::= { ltmHttpProfileEntry 45 }

ltmHttpProfilePassthroughExcessClientHeaders OBJECT-TYPE
	SYNTAX INTEGER {
		false(0),
		true(1)
	}
	MAX-ACCESS read-only
	STATUS current
	DESCRIPTION
		"The state indicating passthrough behavior on seeing excess client headers in this profile."
	::= { ltmHttpProfileEntry 46 }

ltmHttpProfilePassthroughExcessServerHeaders OBJECT-TYPE
	SYNTAX INTEGER {
		false(0),
		true(1)
	}
	MAX-ACCESS read-only
	STATUS current
	DESCRIPTION
		"The state indicating passthrough behavior on seeing excess server headers in this profile."
	::= { ltmHttpProfileEntry 47 }

ltmHttpProfilePassthroughUnknownMethod OBJECT-TYPE
	SYNTAX INTEGER {
		reject(0),
		allow(1),
		passthrough(2)
	}
	MAX-ACCESS read-only
	STATUS current
	DESCRIPTION
		"The state indicating behavior on seeing an unknown method in this profile."
	::= { ltmHttpProfileEntry 48 }

ltmHttpProfileHstsMode OBJECT-TYPE
	SYNTAX INTEGER {
		disabled(0),
		enabled(1)
	}
	MAX-ACCESS read-only
	STATUS current
	DESCRIPTION
		"The state indicating whether the hsts header is included in the HTTP response."
	::= { ltmHttpProfileEntry 49 }

ltmHttpProfileHstsMaximumAge OBJECT-TYPE
	SYNTAX Gauge
	MAX-ACCESS read-only
	STATUS current
	DESCRIPTION
		"The maximum age to present in the hsts header."
	::= { ltmHttpProfileEntry 50 }

ltmHttpProfileHstsIncludeSubdomains OBJECT-TYPE
	SYNTAX INTEGER {
		disabled(0),
		enabled(1)
	}
	MAX-ACCESS read-only
	STATUS current
	DESCRIPTION
		"The state indicating the presence or absence of the includeSubdomains
	        directive in the HTTP header."
	::= { ltmHttpProfileEntry 51 }

ltmHttpProfileHstsPreload OBJECT-TYPE
	SYNTAX INTEGER {
		disabled(0),
		enabled(1)
	}
	MAX-ACCESS read-only
	STATUS current
	DESCRIPTION
		"The state indicating the presence or absence of the preload
	        directive in the HSTS header."
	::= { ltmHttpProfileEntry 52 }

ltmHttpProfileOneConnectStatusReuse OBJECT-TYPE
	SYNTAX LongDisplayString
	MAX-ACCESS read-only
	STATUS current
	DESCRIPTION
		"The 2xx and 4xx HTTP status codes that allow OneConnect server-side reuse."
	::= { ltmHttpProfileEntry 53 }

--==================================================================
-- Profile_http_compress_uri_includes
--==================================================================
ltmCompUriInclNumber OBJECT-TYPE
	SYNTAX INTEGER
	MAX-ACCESS read-only
	STATUS	 deprecated
	DESCRIPTION
		"Deprecated!.
		The number of ltmHttpProfileCompUriIncl entries in the table."
	::= { ltmHttpProfileCompUriIncl 1 }

ltmCompUriInclTable OBJECT-TYPE
	SYNTAX SEQUENCE OF LtmCompUriInclEntry
	MAX-ACCESS not-accessible
	STATUS deprecated
	DESCRIPTION
		"A table containing information of regular expressions used to match
		the request URI part of the client requests during compression.
		A match must be found in at least one of the 'include' fields."
	::= { ltmHttpProfileCompUriIncl 2 }

ltmCompUriInclEntry OBJECT-TYPE
	SYNTAX  LtmCompUriInclEntry
	MAX-ACCESS not-accessible
	STATUS deprecated
	DESCRIPTION
		"Columns in the ltmCompUriIncl Table"
	INDEX {
		ltmCompUriInclName,
		ltmCompUriInclIndex
	}
	::= { ltmCompUriInclTable 1 }

LtmCompUriInclEntry ::=
	SEQUENCE {
        	ltmCompUriInclName                                        LongDisplayString,
        	ltmCompUriInclIndex                                       INTEGER,
        	ltmCompUriInclUri                                         LongDisplayString
	}

ltmCompUriInclName OBJECT-TYPE
	SYNTAX LongDisplayString
	MAX-ACCESS read-only
	STATUS	 deprecated
	DESCRIPTION
		"The name of a HTTP profile."
	::= { ltmCompUriInclEntry 1 }

ltmCompUriInclIndex OBJECT-TYPE
	SYNTAX INTEGER(0..2147483647)
	MAX-ACCESS read-only
	STATUS	 deprecated
	DESCRIPTION
		"The index of the regular expression used to match the request
		URI part of the client requests during compression in
		'include' fields for the specified HTTP profile."
	::= { ltmCompUriInclEntry 2 }

ltmCompUriInclUri OBJECT-TYPE
	SYNTAX LongDisplayString
	MAX-ACCESS read-only
	STATUS	 deprecated
	DESCRIPTION
		"The regular expression used to match the request URI part
		of the client requests during compression in 'include' fields
		for the specified HTTP profile."
	::= { ltmCompUriInclEntry 3 }

--==================================================================
-- Profile_http_compress_uri_excludes
--==================================================================
ltmCompUriExclNumber OBJECT-TYPE
	SYNTAX INTEGER
	MAX-ACCESS read-only
	STATUS	 deprecated
	DESCRIPTION
		"Deprecated!.
		The number of ltmHttpProfileCompUriExcl entries in the table."
	::= { ltmHttpProfileCompUriExcl 1 }

ltmCompUriExclTable OBJECT-TYPE
	SYNTAX SEQUENCE OF LtmCompUriExclEntry
	MAX-ACCESS not-accessible
	STATUS deprecated
	DESCRIPTION
		"A table containing information of regular expressions used to match
		the request URI part of the client requests during compression.
		A match must be found in at least one of the 'exclude' fields."
	::= { ltmHttpProfileCompUriExcl 2 }

ltmCompUriExclEntry OBJECT-TYPE
	SYNTAX  LtmCompUriExclEntry
	MAX-ACCESS not-accessible
	STATUS deprecated
	DESCRIPTION
		"Columns in the ltmCompUriExcl Table"
	INDEX {
		ltmCompUriExclName,
		ltmCompUriExclIndex
	}
	::= { ltmCompUriExclTable 1 }

LtmCompUriExclEntry ::=
	SEQUENCE {
        	ltmCompUriExclName                                        LongDisplayString,
        	ltmCompUriExclIndex                                       INTEGER,
        	ltmCompUriExclUri                                         LongDisplayString
	}

ltmCompUriExclName OBJECT-TYPE
	SYNTAX LongDisplayString
	MAX-ACCESS read-only
	STATUS	 deprecated
	DESCRIPTION
		"The name of a HTTP profile."
	::= { ltmCompUriExclEntry 1 }

ltmCompUriExclIndex OBJECT-TYPE
	SYNTAX INTEGER(0..2147483647)
	MAX-ACCESS read-only
	STATUS	 deprecated
	DESCRIPTION
		"The index of the regular expression used to match the request
		URI part of the client requests during compression in
		'exclude' fields for the specified HTTP profile."
	::= { ltmCompUriExclEntry 2 }

ltmCompUriExclUri OBJECT-TYPE
	SYNTAX LongDisplayString
	MAX-ACCESS read-only
	STATUS	 deprecated
	DESCRIPTION
		"The regular expression used to match the request URI part
		of the client requests during compression in 'exclude' fields
		for the specified HTTP profile."
	::= { ltmCompUriExclEntry 3 }

--==================================================================
-- Profile_http_compress_content_type_includes
--==================================================================
ltmCompContTypeInclNumber OBJECT-TYPE
	SYNTAX INTEGER
	MAX-ACCESS read-only
	STATUS	 deprecated
	DESCRIPTION
		"Deprecated!.
		The number of ltmHttpProfileCompContTypeIncl entries in the table."
	::= { ltmHttpProfileCompContTypeIncl 1 }

ltmCompContTypeInclTable OBJECT-TYPE
	SYNTAX SEQUENCE OF LtmCompContTypeInclEntry
	MAX-ACCESS not-accessible
	STATUS deprecated
	DESCRIPTION
		"A table containing information of regular expressions used to match
		the MIME types in the server response's 'Content-Type:' headers.
		A match must be found in at least one of the 'include' fields."
	::= { ltmHttpProfileCompContTypeIncl 2 }

ltmCompContTypeInclEntry OBJECT-TYPE
	SYNTAX  LtmCompContTypeInclEntry
	MAX-ACCESS not-accessible
	STATUS deprecated
	DESCRIPTION
		"Columns in the ltmCompContTypeIncl Table"
	INDEX {
		ltmCompContTypeInclName,
		ltmCompContTypeInclIndex
	}
	::= { ltmCompContTypeInclTable 1 }

LtmCompContTypeInclEntry ::=
	SEQUENCE {
        	ltmCompContTypeInclName                                   LongDisplayString,
        	ltmCompContTypeInclIndex                                  INTEGER,
        	ltmCompContTypeInclContentType                            LongDisplayString
	}

ltmCompContTypeInclName OBJECT-TYPE
	SYNTAX LongDisplayString
	MAX-ACCESS read-only
	STATUS	 deprecated
	DESCRIPTION
		"The name of a HTTP profile."
	::= { ltmCompContTypeInclEntry 1 }

ltmCompContTypeInclIndex OBJECT-TYPE
	SYNTAX INTEGER(0..2147483647)
	MAX-ACCESS read-only
	STATUS	 deprecated
	DESCRIPTION
		"The index of the regular expression to match the MIME types in the
	        server response's 'Content-Type:' headers in 'include' fields for
		the specified HTTP profile."
	::= { ltmCompContTypeInclEntry 2 }

ltmCompContTypeInclContentType OBJECT-TYPE
	SYNTAX LongDisplayString
	MAX-ACCESS read-only
	STATUS	 deprecated
	DESCRIPTION
		"The regular expression used to match the MIME types in the server
		response's 'Content-Type:' headers in 'include' fields for the
		specified HTTP profile."
	::= { ltmCompContTypeInclEntry 3 }

--==================================================================
-- Profile_http_compress_content_type_excludes
--==================================================================
ltmCompContTypeExclNumber OBJECT-TYPE
	SYNTAX INTEGER
	MAX-ACCESS read-only
	STATUS	 deprecated
	DESCRIPTION
		"Deprecated!.
		The number of ltmHttpProfileCompContTypeExcl entries in the table."
	::= { ltmHttpProfileCompContTypeExcl 1 }

ltmCompContTypeExclTable OBJECT-TYPE
	SYNTAX SEQUENCE OF LtmCompContTypeExclEntry
	MAX-ACCESS not-accessible
	STATUS deprecated
	DESCRIPTION
		"A table containing information of regular expressions used to match
		the MIME types in the server response's 'Content-Type:' headers.
		A match must be found in at least one of the 'exclude' fields."
	::= { ltmHttpProfileCompContTypeExcl 2 }

ltmCompContTypeExclEntry OBJECT-TYPE
	SYNTAX  LtmCompContTypeExclEntry
	MAX-ACCESS not-accessible
	STATUS deprecated
	DESCRIPTION
		"Columns in the ltmCompContTypeExcl Table"
	INDEX {
		ltmCompContTypeExclName,
		ltmCompContTypeExclIndex
	}
	::= { ltmCompContTypeExclTable 1 }

LtmCompContTypeExclEntry ::=
	SEQUENCE {
        	ltmCompContTypeExclName                                   LongDisplayString,
        	ltmCompContTypeExclIndex                                  INTEGER,
        	ltmCompContTypeExclContentType                            LongDisplayString
	}

ltmCompContTypeExclName OBJECT-TYPE
	SYNTAX LongDisplayString
	MAX-ACCESS read-only
	STATUS	 deprecated
	DESCRIPTION
		"The name of a HTTP profile."
	::= { ltmCompContTypeExclEntry 1 }

ltmCompContTypeExclIndex OBJECT-TYPE
	SYNTAX INTEGER(0..2147483647)
	MAX-ACCESS read-only
	STATUS	 deprecated
	DESCRIPTION
		"The index of the regular expression to match the MIME types in the
	        server response's 'Content-Type:' headers in 'exclude' fields for
		the specified HTTP profile."
	::= { ltmCompContTypeExclEntry 2 }

ltmCompContTypeExclContentType OBJECT-TYPE
	SYNTAX LongDisplayString
	MAX-ACCESS read-only
	STATUS	 deprecated
	DESCRIPTION
		"The regular expression used to match the MIME types in the server
		response's 'Content-Type:' headers in 'exclude' fields for the
		specified HTTP profile."
	::= { ltmCompContTypeExclEntry 3 }

--==================================================================
-- Profile_http_stat
--==================================================================
ltmHttpProfileStatResetStats OBJECT-TYPE
	SYNTAX INTEGER
	MAX-ACCESS read-write
	STATUS current
	DESCRIPTION
		"The action to reset resettable statistics data in ltmHttpProfileStat.
		 Setting this value to 1 will reset statistics data.
		 Note, some statistics data may not be reset including data that are incremental counters."
	::= { ltmHttpProfileStat 1 }

ltmHttpProfileStatNumber OBJECT-TYPE
	SYNTAX INTEGER
	MAX-ACCESS read-only
	STATUS current
	DESCRIPTION
		"The number of ltmHttpProfileStat entries in the table."
	::= { ltmHttpProfileStat 2 }

ltmHttpProfileStatTable OBJECT-TYPE
	SYNTAX SEQUENCE OF LtmHttpProfileStatEntry
	MAX-ACCESS not-accessible
	STATUS current
	DESCRIPTION
		"A table containing statistic information of HTTP profiles."
	::= { ltmHttpProfileStat 3 }

ltmHttpProfileStatEntry OBJECT-TYPE
	SYNTAX  LtmHttpProfileStatEntry
	MAX-ACCESS not-accessible
	STATUS current
	DESCRIPTION
		"Columns in the ltmHttpProfileStat Table"
	INDEX {
		ltmHttpProfileStatName
	}
	::= { ltmHttpProfileStatTable 1 }

LtmHttpProfileStatEntry ::=
	SEQUENCE {
        	ltmHttpProfileStatName                                    LongDisplayString,
        	ltmHttpProfileStatCookiePersistInserts                    Counter64,
        	ltmHttpProfileStatResp2xxCnt                              Counter64,
        	ltmHttpProfileStatResp3xxCnt                              Counter64,
        	ltmHttpProfileStatResp4xxCnt                              Counter64,
        	ltmHttpProfileStatResp5xxCnt                              Counter64,
        	ltmHttpProfileStatNumberReqs                              Counter64,
        	ltmHttpProfileStatGetReqs                                 Counter64,
        	ltmHttpProfileStatPostReqs                                Counter64,
        	ltmHttpProfileStatV9Reqs                                  Counter64,
        	ltmHttpProfileStatV10Reqs                                 Counter64,
        	ltmHttpProfileStatV11Reqs                                 Counter64,
        	ltmHttpProfileStatV9Resp                                  Counter64,
        	ltmHttpProfileStatV10Resp                                 Counter64,
        	ltmHttpProfileStatV11Resp                                 Counter64,
        	ltmHttpProfileStatMaxKeepaliveReq                         Counter64,
        	ltmHttpProfileStatRespBucket1k                            Counter64,
        	ltmHttpProfileStatRespBucket4k                            Counter64,
        	ltmHttpProfileStatRespBucket16k                           Counter64,
        	ltmHttpProfileStatRespBucket32k                           Counter64,
        	ltmHttpProfileStatPrecompressBytes                        Counter64,
        	ltmHttpProfileStatPostcompressBytes                       Counter64,
        	ltmHttpProfileStatNullCompressBytes                       Counter64,
        	ltmHttpProfileStatHtmlPrecompressBytes                    Counter64,
        	ltmHttpProfileStatHtmlPostcompressBytes                   Counter64,
        	ltmHttpProfileStatCssPrecompressBytes                     Counter64,
        	ltmHttpProfileStatCssPostcompressBytes                    Counter64,
        	ltmHttpProfileStatJsPrecompressBytes                      Counter64,
        	ltmHttpProfileStatJsPostcompressBytes                     Counter64,
        	ltmHttpProfileStatXmlPrecompressBytes                     Counter64,
        	ltmHttpProfileStatXmlPostcompressBytes                    Counter64,
        	ltmHttpProfileStatSgmlPrecompressBytes                    Counter64,
        	ltmHttpProfileStatSgmlPostcompressBytes                   Counter64,
        	ltmHttpProfileStatPlainPrecompressBytes                   Counter64,
        	ltmHttpProfileStatPlainPostcompressBytes                  Counter64,
        	ltmHttpProfileStatOctetPrecompressBytes                   Counter64,
        	ltmHttpProfileStatOctetPostcompressBytes                  Counter64,
        	ltmHttpProfileStatImagePrecompressBytes                   Counter64,
        	ltmHttpProfileStatImagePostcompressBytes                  Counter64,
        	ltmHttpProfileStatVideoPrecompressBytes                   Counter64,
        	ltmHttpProfileStatVideoPostcompressBytes                  Counter64,
        	ltmHttpProfileStatAudioPrecompressBytes                   Counter64,
        	ltmHttpProfileStatAudioPostcompressBytes                  Counter64,
        	ltmHttpProfileStatOtherPrecompressBytes                   Counter64,
        	ltmHttpProfileStatOtherPostcompressBytes                  Counter64,
        	ltmHttpProfileStatRamcacheHits                            Counter64,
        	ltmHttpProfileStatRamcacheMisses                          Counter64,
        	ltmHttpProfileStatRamcacheMissesAll                       Counter64,
        	ltmHttpProfileStatRamcacheHitBytes                        Counter64,
        	ltmHttpProfileStatRamcacheMissBytes                       Counter64,
        	ltmHttpProfileStatRamcacheMissBytesAll                    Counter64,
        	ltmHttpProfileStatRamcacheSize                            Counter64,
        	ltmHttpProfileStatRamcacheCount                           Counter64,
        	ltmHttpProfileStatRamcacheEvictions                       Counter64,
        	ltmHttpProfileStatRespBucket64k                           Counter64,
        	ltmHttpProfileStatPassthroughIrule                        Counter64,
        	ltmHttpProfileStatPassthroughConnect                      Counter64,
        	ltmHttpProfileStatPassthroughWebSockets                   Counter64,
        	ltmHttpProfileStatPassthroughOversizeClientHeaders        Counter64,
        	ltmHttpProfileStatPassthroughOversizeServerHeaders        Counter64,
        	ltmHttpProfileStatPassthroughExcessClientHeaders          Counter64,
        	ltmHttpProfileStatPassthroughExcessServerHeaders          Counter64,
        	ltmHttpProfileStatPassthroughUnknownMethod                Counter64,
        	ltmHttpProfileStatPassthroughPipeline                     Counter64
	}

ltmHttpProfileStatName OBJECT-TYPE
	SYNTAX LongDisplayString
	MAX-ACCESS read-only
	STATUS current
	DESCRIPTION
		"The name of a HTTP profile."
	::= { ltmHttpProfileStatEntry 1 }

ltmHttpProfileStatCookiePersistInserts OBJECT-TYPE
	SYNTAX Counter64
	MAX-ACCESS read-only
	STATUS current
	DESCRIPTION
		"The number of successful attempts to insert HTTP headers
		 for cookie persistence (set-cookie header insertions)."
	::= { ltmHttpProfileStatEntry 2 }

ltmHttpProfileStatResp2xxCnt OBJECT-TYPE
	SYNTAX Counter64
	MAX-ACCESS read-only
	STATUS current
	DESCRIPTION
		"The number of server-side responses in range of 200 to 206
		 (successful responses)"
	::= { ltmHttpProfileStatEntry 3 }

ltmHttpProfileStatResp3xxCnt OBJECT-TYPE
	SYNTAX Counter64
	MAX-ACCESS read-only
	STATUS current
	DESCRIPTION
		"The number of server-side responses in range of 300 to 307
		 (redirection responses)."
	::= { ltmHttpProfileStatEntry 4 }

ltmHttpProfileStatResp4xxCnt OBJECT-TYPE
	SYNTAX Counter64
	MAX-ACCESS read-only
	STATUS current
	DESCRIPTION
		"The number of server-side responses in range of 400 to 417
		 (client errors)."
	::= { ltmHttpProfileStatEntry 5 }

ltmHttpProfileStatResp5xxCnt OBJECT-TYPE
	SYNTAX Counter64
	MAX-ACCESS read-only
	STATUS current
	DESCRIPTION
		"The number of server-side responses in range of 500 to 505
		 (server errors)."
	::= { ltmHttpProfileStatEntry 6 }

ltmHttpProfileStatNumberReqs OBJECT-TYPE
	SYNTAX Counter64
	MAX-ACCESS read-only
	STATUS current
	DESCRIPTION
		"The total number of HTTP requests."
	::= { ltmHttpProfileStatEntry 7 }

ltmHttpProfileStatGetReqs OBJECT-TYPE
	SYNTAX Counter64
	MAX-ACCESS read-only
	STATUS current
	DESCRIPTION
		"The total number of HTTP get requests."
	::= { ltmHttpProfileStatEntry 8 }

ltmHttpProfileStatPostReqs OBJECT-TYPE
	SYNTAX Counter64
	MAX-ACCESS read-only
	STATUS current
	DESCRIPTION
		"The total number of HTTP post requests."
	::= { ltmHttpProfileStatEntry 9 }

ltmHttpProfileStatV9Reqs OBJECT-TYPE
	SYNTAX Counter64
	MAX-ACCESS read-only
	STATUS current
	DESCRIPTION
		"The total number of version 9 requests."
	::= { ltmHttpProfileStatEntry 10 }

ltmHttpProfileStatV10Reqs OBJECT-TYPE
	SYNTAX Counter64
	MAX-ACCESS read-only
	STATUS current
	DESCRIPTION
		"The total number of version 10 requests."
	::= { ltmHttpProfileStatEntry 11 }

ltmHttpProfileStatV11Reqs OBJECT-TYPE
	SYNTAX Counter64
	MAX-ACCESS read-only
	STATUS current
	DESCRIPTION
		"The total number of version 11 requests."
	::= { ltmHttpProfileStatEntry 12 }

ltmHttpProfileStatV9Resp OBJECT-TYPE
	SYNTAX Counter64
	MAX-ACCESS read-only
	STATUS current
	DESCRIPTION
		"The total number of version 9 responses."
	::= { ltmHttpProfileStatEntry 13 }

ltmHttpProfileStatV10Resp OBJECT-TYPE
	SYNTAX Counter64
	MAX-ACCESS read-only
	STATUS current
	DESCRIPTION
		"The total number of version 10 responses."
	::= { ltmHttpProfileStatEntry 14 }

ltmHttpProfileStatV11Resp OBJECT-TYPE
	SYNTAX Counter64
	MAX-ACCESS read-only
	STATUS current
	DESCRIPTION
		"The total number of version 11 responses."
	::= { ltmHttpProfileStatEntry 15 }

ltmHttpProfileStatMaxKeepaliveReq OBJECT-TYPE
	SYNTAX Counter64
	MAX-ACCESS read-only
	STATUS current
	DESCRIPTION
		"The maximum number of requests made in a connection."
	::= { ltmHttpProfileStatEntry 16 }

ltmHttpProfileStatRespBucket1k OBJECT-TYPE
	SYNTAX Counter64
	MAX-ACCESS read-only
	STATUS current
	DESCRIPTION
		"The number of responses under 1k."
	::= { ltmHttpProfileStatEntry 17 }

ltmHttpProfileStatRespBucket4k OBJECT-TYPE
	SYNTAX Counter64
	MAX-ACCESS read-only
	STATUS current
	DESCRIPTION
		"The number of responses under 1 - 4k."
	::= { ltmHttpProfileStatEntry 18 }

ltmHttpProfileStatRespBucket16k OBJECT-TYPE
	SYNTAX Counter64
	MAX-ACCESS read-only
	STATUS current
	DESCRIPTION
		"The number of responses under 4 - 16k."
	::= { ltmHttpProfileStatEntry 19 }

ltmHttpProfileStatRespBucket32k OBJECT-TYPE
	SYNTAX Counter64
	MAX-ACCESS read-only
	STATUS current
	DESCRIPTION
		"The number of responses under 16 - 32k."
	::= { ltmHttpProfileStatEntry 20 }

ltmHttpProfileStatPrecompressBytes OBJECT-TYPE
	SYNTAX Counter64
	MAX-ACCESS read-only
	STATUS	 deprecated
	DESCRIPTION
		"Deprecated!  The number of response bytes before compression has taken place."
	::= { ltmHttpProfileStatEntry 21 }

ltmHttpProfileStatPostcompressBytes OBJECT-TYPE
	SYNTAX Counter64
	MAX-ACCESS read-only
	STATUS	 deprecated
	DESCRIPTION
		"Deprecated!  The number of response bytes after compression has taken place."
	::= { ltmHttpProfileStatEntry 22 }

ltmHttpProfileStatNullCompressBytes OBJECT-TYPE
	SYNTAX Counter64
	MAX-ACCESS read-only
	STATUS	 deprecated
	DESCRIPTION
		"Deprecated!  The number of bytes subjected to NULL compression (for license enforcement)."
	::= { ltmHttpProfileStatEntry 23 }

ltmHttpProfileStatHtmlPrecompressBytes OBJECT-TYPE
	SYNTAX Counter64
	MAX-ACCESS read-only
	STATUS	 deprecated
	DESCRIPTION
		"Deprecated!  The number of pre-compressed bytes for the MIME-Types: HTML."
	::= { ltmHttpProfileStatEntry 24 }

ltmHttpProfileStatHtmlPostcompressBytes OBJECT-TYPE
	SYNTAX Counter64
	MAX-ACCESS read-only
	STATUS	 deprecated
	DESCRIPTION
		"Deprecated!  The number of post-compressed bytes for the MIME-Types: HTML."
	::= { ltmHttpProfileStatEntry 25 }

ltmHttpProfileStatCssPrecompressBytes OBJECT-TYPE
	SYNTAX Counter64
	MAX-ACCESS read-only
	STATUS	 deprecated
	DESCRIPTION
		"Deprecated!  The number of pre-compressed bytes for the MIME-Types: CSS."
	::= { ltmHttpProfileStatEntry 26 }

ltmHttpProfileStatCssPostcompressBytes OBJECT-TYPE
	SYNTAX Counter64
	MAX-ACCESS read-only
	STATUS	 deprecated
	DESCRIPTION
		"Deprecated!  The number of post-compressed bytes for the MIME-Types: CSS."
	::= { ltmHttpProfileStatEntry 27 }

ltmHttpProfileStatJsPrecompressBytes OBJECT-TYPE
	SYNTAX Counter64
	MAX-ACCESS read-only
	STATUS	 deprecated
	DESCRIPTION
		"Deprecated!  The number of pre-compressed bytes for the MIME-Types: Javascript."
	::= { ltmHttpProfileStatEntry 28 }

ltmHttpProfileStatJsPostcompressBytes OBJECT-TYPE
	SYNTAX Counter64
	MAX-ACCESS read-only
	STATUS	 deprecated
	DESCRIPTION
		"Deprecated!  The number of post-compressed bytes for the MIME-Types: Javascript."
	::= { ltmHttpProfileStatEntry 29 }

ltmHttpProfileStatXmlPrecompressBytes OBJECT-TYPE
	SYNTAX Counter64
	MAX-ACCESS read-only
	STATUS	 deprecated
	DESCRIPTION
		"Deprecated!  The number of pre-compressed bytes for the MIME-Types: XML."
	::= { ltmHttpProfileStatEntry 30 }

ltmHttpProfileStatXmlPostcompressBytes OBJECT-TYPE
	SYNTAX Counter64
	MAX-ACCESS read-only
	STATUS	 deprecated
	DESCRIPTION
		"Deprecated!  The number of post-compressed bytes for the MIME-Types: XML."
	::= { ltmHttpProfileStatEntry 31 }

ltmHttpProfileStatSgmlPrecompressBytes OBJECT-TYPE
	SYNTAX Counter64
	MAX-ACCESS read-only
	STATUS	 deprecated
	DESCRIPTION
		"Deprecated!  The number of pre-compressed bytes for the MIME-Types: SGML."
	::= { ltmHttpProfileStatEntry 32 }

ltmHttpProfileStatSgmlPostcompressBytes OBJECT-TYPE
	SYNTAX Counter64
	MAX-ACCESS read-only
	STATUS	 deprecated
	DESCRIPTION
		"Deprecated!  The number of post-compressed bytes for the MIME-Types: SGML."
	::= { ltmHttpProfileStatEntry 33 }

ltmHttpProfileStatPlainPrecompressBytes OBJECT-TYPE
	SYNTAX Counter64
	MAX-ACCESS read-only
	STATUS	 deprecated
	DESCRIPTION
		"Deprecated!  The number of pre-compressed bytes for the MIME-Types: Plain."
	::= { ltmHttpProfileStatEntry 34 }

ltmHttpProfileStatPlainPostcompressBytes OBJECT-TYPE
	SYNTAX Counter64
	MAX-ACCESS read-only
	STATUS	 deprecated
	DESCRIPTION
		"Deprecated!  The number of post-compressed bytes for the MIME-Types: Plain."
	::= { ltmHttpProfileStatEntry 35 }

ltmHttpProfileStatOctetPrecompressBytes OBJECT-TYPE
	SYNTAX Counter64
	MAX-ACCESS read-only
	STATUS	 deprecated
	DESCRIPTION
		"Deprecated!  The number of pre-compressed bytes for the MIME-Types: Octet stream."
	::= { ltmHttpProfileStatEntry 36 }

ltmHttpProfileStatOctetPostcompressBytes OBJECT-TYPE
	SYNTAX Counter64
	MAX-ACCESS read-only
	STATUS	 deprecated
	DESCRIPTION
		"Deprecated!  The number of post-compressed bytes for the MIME-Types: Octet stream."
	::= { ltmHttpProfileStatEntry 37 }

ltmHttpProfileStatImagePrecompressBytes OBJECT-TYPE
	SYNTAX Counter64
	MAX-ACCESS read-only
	STATUS	 deprecated
	DESCRIPTION
		"Deprecated!  The number of pre-compressed bytes for the MIME-Types: Images."
	::= { ltmHttpProfileStatEntry 38 }

ltmHttpProfileStatImagePostcompressBytes OBJECT-TYPE
	SYNTAX Counter64
	MAX-ACCESS read-only
	STATUS	 deprecated
	DESCRIPTION
		"Deprecated!  The number of post-compressed bytes for the MIME-Types: Images."
	::= { ltmHttpProfileStatEntry 39 }

ltmHttpProfileStatVideoPrecompressBytes OBJECT-TYPE
	SYNTAX Counter64
	MAX-ACCESS read-only
	STATUS	 deprecated
	DESCRIPTION
		"Deprecated!  The number of pre-compressed bytes for the MIME-Types: Video files."
	::= { ltmHttpProfileStatEntry 40 }

ltmHttpProfileStatVideoPostcompressBytes OBJECT-TYPE
	SYNTAX Counter64
	MAX-ACCESS read-only
	STATUS	 deprecated
	DESCRIPTION
		"Deprecated!  The number of post-compressed bytes for the MIME-Types: Video files."
	::= { ltmHttpProfileStatEntry 41 }

ltmHttpProfileStatAudioPrecompressBytes OBJECT-TYPE
	SYNTAX Counter64
	MAX-ACCESS read-only
	STATUS	 deprecated
	DESCRIPTION
		"Deprecated!  The number of pre-compressed bytes for the MIME-Types: Audio files."
	::= { ltmHttpProfileStatEntry 42 }

ltmHttpProfileStatAudioPostcompressBytes OBJECT-TYPE
	SYNTAX Counter64
	MAX-ACCESS read-only
	STATUS	 deprecated
	DESCRIPTION
		"Deprecated!  The number of post-compressed bytes for the MIME-Types: Audio files."
	::= { ltmHttpProfileStatEntry 43 }

ltmHttpProfileStatOtherPrecompressBytes OBJECT-TYPE
	SYNTAX Counter64
	MAX-ACCESS read-only
	STATUS	 deprecated
	DESCRIPTION
		"Deprecated!  The number of pre-compressed bytes for the MIME-Types: other than
		HTML, CSS, Javascript, XML, SGML, Plain, Images, Video files,
		Audio files."
	::= { ltmHttpProfileStatEntry 44 }

ltmHttpProfileStatOtherPostcompressBytes OBJECT-TYPE
	SYNTAX Counter64
	MAX-ACCESS read-only
	STATUS	 deprecated
	DESCRIPTION
		"Deprecated!  The number of post-compressed bytes for the MIME-Types: other than
		HTML, CSS, Javascript, XML, SGML, Plain, Images, Video files,
		Audio files."
	::= { ltmHttpProfileStatEntry 45 }

ltmHttpProfileStatRamcacheHits OBJECT-TYPE
	SYNTAX Counter64
	MAX-ACCESS read-only
	STATUS	 deprecated
	DESCRIPTION
		"Deprecated!  The number of RAM cache hits."
	::= { ltmHttpProfileStatEntry 46 }

ltmHttpProfileStatRamcacheMisses OBJECT-TYPE
	SYNTAX Counter64
	MAX-ACCESS read-only
	STATUS	 deprecated
	DESCRIPTION
		"Deprecated!  The number of RAM cache misses, excluding un-cacheable data."
	::= { ltmHttpProfileStatEntry 47 }

ltmHttpProfileStatRamcacheMissesAll OBJECT-TYPE
	SYNTAX Counter64
	MAX-ACCESS read-only
	STATUS	 deprecated
	DESCRIPTION
		"Deprecated!  The total number of RAM cache misses."
	::= { ltmHttpProfileStatEntry 48 }

ltmHttpProfileStatRamcacheHitBytes OBJECT-TYPE
	SYNTAX Counter64
	MAX-ACCESS read-only
	STATUS	 deprecated
	DESCRIPTION
		"Deprecated!  The number of RAM cache hits in bytes."
	::= { ltmHttpProfileStatEntry 49 }

ltmHttpProfileStatRamcacheMissBytes OBJECT-TYPE
	SYNTAX Counter64
	MAX-ACCESS read-only
	STATUS	 deprecated
	DESCRIPTION
		"Deprecated!  The number of RAM cache misses in bytes, excluding un-cacheable data."
	::= { ltmHttpProfileStatEntry 50 }

ltmHttpProfileStatRamcacheMissBytesAll OBJECT-TYPE
	SYNTAX Counter64
	MAX-ACCESS read-only
	STATUS	 deprecated
	DESCRIPTION
		"Deprecated!  The total number of RAM cache misses in bytes."
	::= { ltmHttpProfileStatEntry 51 }

ltmHttpProfileStatRamcacheSize OBJECT-TYPE
	SYNTAX Counter64
	MAX-ACCESS read-only
	STATUS	 deprecated
	DESCRIPTION
		"Deprecated!  The Ram cache current size."
	::= { ltmHttpProfileStatEntry 52 }

ltmHttpProfileStatRamcacheCount OBJECT-TYPE
	SYNTAX Counter64
	MAX-ACCESS read-only
	STATUS	 deprecated
	DESCRIPTION
		"Deprecated!  The number of items stored in Ram cache."
	::= { ltmHttpProfileStatEntry 53 }

ltmHttpProfileStatRamcacheEvictions OBJECT-TYPE
	SYNTAX Counter64
	MAX-ACCESS read-only
	STATUS	 deprecated
	DESCRIPTION
		"Deprecated!  The number of Ram cache evictions."
	::= { ltmHttpProfileStatEntry 54 }

ltmHttpProfileStatRespBucket64k OBJECT-TYPE
	SYNTAX Counter64
	MAX-ACCESS read-only
	STATUS	 deprecated
	DESCRIPTION
		"Deprecated! Please see the new larger bucket sizes"
	::= { ltmHttpProfileStatEntry 55 }

ltmHttpProfileStatPassthroughIrule OBJECT-TYPE
	SYNTAX Counter64
	MAX-ACCESS read-only
	STATUS current
	DESCRIPTION
		"The number of HTTP::disable's leading to pass through mode."
	::= { ltmHttpProfileStatEntry 56 }

ltmHttpProfileStatPassthroughConnect OBJECT-TYPE
	SYNTAX Counter64
	MAX-ACCESS read-only
	STATUS current
	DESCRIPTION
		"The number of CONNECT methods leading to pass through mode."
	::= { ltmHttpProfileStatEntry 57 }

ltmHttpProfileStatPassthroughWebSockets OBJECT-TYPE
	SYNTAX Counter64
	MAX-ACCESS read-only
	STATUS current
	DESCRIPTION
		"The number of 100 Switching Protocols leading to pass through mode."
	::= { ltmHttpProfileStatEntry 58 }

ltmHttpProfileStatPassthroughOversizeClientHeaders OBJECT-TYPE
	SYNTAX Counter64
	MAX-ACCESS read-only
	STATUS current
	DESCRIPTION
		"The number of too-large client headers requests causing pass through mode."
	::= { ltmHttpProfileStatEntry 59 }

ltmHttpProfileStatPassthroughOversizeServerHeaders OBJECT-TYPE
	SYNTAX Counter64
	MAX-ACCESS read-only
	STATUS current
	DESCRIPTION
		"The number of too-large server headers responses causing pass through mode."
	::= { ltmHttpProfileStatEntry 60 }

ltmHttpProfileStatPassthroughExcessClientHeaders OBJECT-TYPE
	SYNTAX Counter64
	MAX-ACCESS read-only
	STATUS current
	DESCRIPTION
		"The number of too many client headers requests causing pass through mode."
	::= { ltmHttpProfileStatEntry 61 }

ltmHttpProfileStatPassthroughExcessServerHeaders OBJECT-TYPE
	SYNTAX Counter64
	MAX-ACCESS read-only
	STATUS current
	DESCRIPTION
		"The number of too many server headers responses causing pass through mode."
	::= { ltmHttpProfileStatEntry 62 }

ltmHttpProfileStatPassthroughUnknownMethod OBJECT-TYPE
	SYNTAX Counter64
	MAX-ACCESS read-only
	STATUS current
	DESCRIPTION
		"The number of unknown methods leading to pass through mode."
	::= { ltmHttpProfileStatEntry 63 }

ltmHttpProfileStatPassthroughPipeline OBJECT-TYPE
	SYNTAX Counter64
	MAX-ACCESS read-only
	STATUS current
	DESCRIPTION
		"The number of pipelined requests leading to pass through mode."
	::= { ltmHttpProfileStatEntry 64 }

--==================================================================
-- Profile_persist
--==================================================================
ltmPersistProfileNumber OBJECT-TYPE
	SYNTAX INTEGER
	MAX-ACCESS read-only
	STATUS current
	DESCRIPTION
		"The number of ltmPersistProfile entries in the table."
	::= { ltmPersistProfile 1 }

ltmPersistProfileTable OBJECT-TYPE
	SYNTAX SEQUENCE OF LtmPersistProfileEntry
	MAX-ACCESS not-accessible
	STATUS current
	DESCRIPTION
		"A table containing information of persistent profile."
	::= { ltmPersistProfile 2 }

ltmPersistProfileEntry OBJECT-TYPE
	SYNTAX  LtmPersistProfileEntry
	MAX-ACCESS not-accessible
	STATUS current
	DESCRIPTION
		"Columns in the ltmPersistProfile Table"
	INDEX {
		ltmPersistProfileName
	}
	::= { ltmPersistProfileTable 1 }

LtmPersistProfileEntry ::=
	SEQUENCE {
        	ltmPersistProfileName                                     LongDisplayString,
        	ltmPersistProfileConfigSource                             INTEGER,
        	ltmPersistProfileDefaultName                              LongDisplayString,
        	ltmPersistProfileMode                                     INTEGER,
        	ltmPersistProfileMirror                                   INTEGER,
        	ltmPersistProfileTimeout                                  Gauge,
        	ltmPersistProfileMaskType                                 InetAddressType,
        	ltmPersistProfileMask                                     InetAddress,
        	ltmPersistProfileCookieMethod                             INTEGER,
        	ltmPersistProfileCookieName                               LongDisplayString,
        	ltmPersistProfileCookieExpiration                         Gauge,
        	ltmPersistProfileCookieHashOffset                         INTEGER,
        	ltmPersistProfileCookieHashLength                         INTEGER,
        	ltmPersistProfileMsrdpNoSessionDir                        INTEGER,
        	ltmPersistProfileMapProxies                               INTEGER,
        	ltmPersistProfileAcrossServices                           INTEGER,
        	ltmPersistProfileAcrossVirtuals                           INTEGER,
        	ltmPersistProfileAcrossPools                              INTEGER,
        	ltmPersistProfileUieRule                                  LongDisplayString,
        	ltmPersistProfileSipInfo                                  LongDisplayString,
        	ltmPersistProfileCookieHttpOnly                           INTEGER,
        	ltmPersistProfileCookieSecure                             INTEGER
	}

ltmPersistProfileName OBJECT-TYPE
	SYNTAX LongDisplayString
	MAX-ACCESS read-only
	STATUS current
	DESCRIPTION
		"The name of a persist profile."
	::= { ltmPersistProfileEntry 1 }

ltmPersistProfileConfigSource OBJECT-TYPE
	SYNTAX INTEGER {
		usercfg(0),
		basecfg(1)
	}
	MAX-ACCESS read-only
	STATUS current
	DESCRIPTION
		"The state that specifies whether this is a base/pre-configured profile
		or user defined profile."
	::= { ltmPersistProfileEntry 2 }

ltmPersistProfileDefaultName OBJECT-TYPE
	SYNTAX LongDisplayString
	MAX-ACCESS read-only
	STATUS current
	DESCRIPTION
		"The name of the profile from which the specified profile derives
		its attribute default values."
	::= { ltmPersistProfileEntry 3 }

ltmPersistProfileMode OBJECT-TYPE
	SYNTAX INTEGER {
		none(0),
		srcaddr(1),
		dstaddr(2),
		cookie(3),
		msrdp(4),
		sslsid(5),
		sip(6),
		uie(7),
		hash(8),
		host(9)
	}
	MAX-ACCESS read-only
	STATUS current
	DESCRIPTION
		"The type of persistence."
	::= { ltmPersistProfileEntry 4 }

ltmPersistProfileMirror OBJECT-TYPE
	SYNTAX INTEGER {
		false(0),
		true(1)
	}
	MAX-ACCESS read-only
	STATUS current
	DESCRIPTION
		"The state of mirror persistence records."
	::= { ltmPersistProfileEntry 5 }

ltmPersistProfileTimeout OBJECT-TYPE
	SYNTAX Gauge
	MAX-ACCESS read-only
	STATUS current
	DESCRIPTION
		"The value (in seconds) to timeout persist entry."
	::= { ltmPersistProfileEntry 6 }

ltmPersistProfileMaskType OBJECT-TYPE
	SYNTAX InetAddressType
	MAX-ACCESS read-only
	STATUS current
	DESCRIPTION
		"The IP address type of ltmPersistMask"
	::= { ltmPersistProfileEntry 7 }

ltmPersistProfileMask OBJECT-TYPE
	SYNTAX InetAddress
	MAX-ACCESS read-only
	STATUS current
	DESCRIPTION
		"The source/destination address mask. It is interpreted
		within the context of a ltmPersistMaskType value."
	::= { ltmPersistProfileEntry 8 }

ltmPersistProfileCookieMethod OBJECT-TYPE
	SYNTAX INTEGER {
		unspecified(0),
		insert(1),
		rewrite(2),
		passive(3),
		hash(4)
	}
	MAX-ACCESS read-only
	STATUS current
	DESCRIPTION
		"The type of cookie persistence."
	::= { ltmPersistProfileEntry 9 }

ltmPersistProfileCookieName OBJECT-TYPE
	SYNTAX LongDisplayString
	MAX-ACCESS read-only
	STATUS current
	DESCRIPTION
		"The name of cookie."
	::= { ltmPersistProfileEntry 10 }

ltmPersistProfileCookieExpiration OBJECT-TYPE
	SYNTAX Gauge
	MAX-ACCESS read-only
	STATUS current
	DESCRIPTION
		"The cookie expiration in seconds."
	::= { ltmPersistProfileEntry 11 }

ltmPersistProfileCookieHashOffset OBJECT-TYPE
	SYNTAX INTEGER
	MAX-ACCESS read-only
	STATUS current
	DESCRIPTION
		"The offset of cookie for hash mode."
	::= { ltmPersistProfileEntry 12 }

ltmPersistProfileCookieHashLength OBJECT-TYPE
	SYNTAX INTEGER
	MAX-ACCESS read-only
	STATUS current
	DESCRIPTION
		"The length of cookie for hash mode."
	::= { ltmPersistProfileEntry 13 }

ltmPersistProfileMsrdpNoSessionDir OBJECT-TYPE
	SYNTAX INTEGER {
		false(0),
		true(1)
	}
	MAX-ACCESS read-only
	STATUS current
	DESCRIPTION
		"This object indicates MS terminal services has been configured
		without a session directory and causes the initial MSRDP
		connection to be load-balanced."
	::= { ltmPersistProfileEntry 14 }

ltmPersistProfileMapProxies OBJECT-TYPE
	SYNTAX INTEGER {
		false(0),
		true(1)
	}
	MAX-ACCESS read-only
	STATUS current
	DESCRIPTION
		"This object indicates whether we should map known proxies when
		the persistence mode is src_addr."
	::= { ltmPersistProfileEntry 15 }

ltmPersistProfileAcrossServices OBJECT-TYPE
	SYNTAX INTEGER {
		false(0),
		true(1)
	}
	MAX-ACCESS read-only
	STATUS current
	DESCRIPTION
		"This object indicates whether the persistence entries added under
		this profile are available across services."
	::= { ltmPersistProfileEntry 16 }

ltmPersistProfileAcrossVirtuals OBJECT-TYPE
	SYNTAX INTEGER {
		false(0),
		true(1)
	}
	MAX-ACCESS read-only
	STATUS current
	DESCRIPTION
		"This object indicates whether the persistence entries added under
		this profile are available across virtuals."
	::= { ltmPersistProfileEntry 17 }

ltmPersistProfileAcrossPools OBJECT-TYPE
	SYNTAX INTEGER {
		false(0),
		true(1)
	}
	MAX-ACCESS read-only
	STATUS current
	DESCRIPTION
		"This object indicates whether the persistence entries added under
		this profile are available across pools."
	::= { ltmPersistProfileEntry 18 }

ltmPersistProfileUieRule OBJECT-TYPE
	SYNTAX LongDisplayString
	MAX-ACCESS read-only
	STATUS current
	DESCRIPTION
		"The rule name for UIE mode."
	::= { ltmPersistProfileEntry 19 }

ltmPersistProfileSipInfo OBJECT-TYPE
	SYNTAX LongDisplayString
	MAX-ACCESS read-only
	STATUS current
	DESCRIPTION
		"The SIP header name for persisting in the specified profile."
	::= { ltmPersistProfileEntry 20 }

ltmPersistProfileCookieHttpOnly OBJECT-TYPE
	SYNTAX INTEGER {
		disabled(0),
		enabled(1)
	}
	MAX-ACCESS read-only
	STATUS current
	DESCRIPTION
		"The state of cookie HTTP Only attribute."
	::= { ltmPersistProfileEntry 21 }

ltmPersistProfileCookieSecure OBJECT-TYPE
	SYNTAX INTEGER {
		disabled(0),
		enabled(1)
	}
	MAX-ACCESS read-only
	STATUS current
	DESCRIPTION
		"The state of cookie Secure attribute."
	::= { ltmPersistProfileEntry 22 }

--==================================================================
-- Profile_stream
--==================================================================
ltmStreamProfileNumber OBJECT-TYPE
	SYNTAX INTEGER
	MAX-ACCESS read-only
	STATUS current
	DESCRIPTION
		"The number of ltmStreamProfile entries in the table."
	::= { ltmStreamProfile 1 }

ltmStreamProfileTable OBJECT-TYPE
	SYNTAX SEQUENCE OF LtmStreamProfileEntry
	MAX-ACCESS not-accessible
	STATUS current
	DESCRIPTION
		"A table containing information of stream profile."
	::= { ltmStreamProfile 2 }

ltmStreamProfileEntry OBJECT-TYPE
	SYNTAX  LtmStreamProfileEntry
	MAX-ACCESS not-accessible
	STATUS current
	DESCRIPTION
		"Columns in the ltmStreamProfile Table"
	INDEX {
		ltmStreamProfileName
	}
	::= { ltmStreamProfileTable 1 }

LtmStreamProfileEntry ::=
	SEQUENCE {
        	ltmStreamProfileName                                      LongDisplayString,
        	ltmStreamProfileConfigSource                              INTEGER,
        	ltmStreamProfileDefaultName                               LongDisplayString,
        	ltmStreamProfileSource                                    LongDisplayString,
        	ltmStreamProfileTarget                                    LongDisplayString
	}

ltmStreamProfileName OBJECT-TYPE
	SYNTAX LongDisplayString
	MAX-ACCESS read-only
	STATUS current
	DESCRIPTION
		"The name of a stream profile."
	::= { ltmStreamProfileEntry 1 }

ltmStreamProfileConfigSource OBJECT-TYPE
	SYNTAX INTEGER {
		usercfg(0),
		basecfg(1)
	}
	MAX-ACCESS read-only
	STATUS current
	DESCRIPTION
		"The state that specifies whether this is a base/pre-configured profile
		or user defined profile."
	::= { ltmStreamProfileEntry 2 }

ltmStreamProfileDefaultName OBJECT-TYPE
	SYNTAX LongDisplayString
	MAX-ACCESS read-only
	STATUS current
	DESCRIPTION
		"The name of the profile from which the specified profile derives
		its attribute default values."
	::= { ltmStreamProfileEntry 3 }

ltmStreamProfileSource OBJECT-TYPE
	SYNTAX LongDisplayString
	MAX-ACCESS read-only
	STATUS current
	DESCRIPTION
		"The source string to search for."
	::= { ltmStreamProfileEntry 4 }

ltmStreamProfileTarget OBJECT-TYPE
	SYNTAX LongDisplayString
	MAX-ACCESS read-only
	STATUS current
	DESCRIPTION
		"The target string to replace."
	::= { ltmStreamProfileEntry 5 }

--==================================================================
-- Profile_stream_stat
--==================================================================
ltmStreamProfileStatResetStats OBJECT-TYPE
	SYNTAX INTEGER
	MAX-ACCESS read-write
	STATUS current
	DESCRIPTION
		"The action to reset resettable statistics data in ltmStreamProfileStat.
		 Setting this value to 1 will reset statistics data.
		 Note, some statistics data may not be reset including data that are incremental counters."
	::= { ltmStreamProfileStat 1 }

ltmStreamProfileStatNumber OBJECT-TYPE
	SYNTAX INTEGER
	MAX-ACCESS read-only
	STATUS current
	DESCRIPTION
		"The number of ltmStreamProfileStat entries in the table."
	::= { ltmStreamProfileStat 2 }

ltmStreamProfileStatTable OBJECT-TYPE
	SYNTAX SEQUENCE OF LtmStreamProfileStatEntry
	MAX-ACCESS not-accessible
	STATUS current
	DESCRIPTION
		"A table containing statistic information of stream profile."
	::= { ltmStreamProfileStat 3 }

ltmStreamProfileStatEntry OBJECT-TYPE
	SYNTAX  LtmStreamProfileStatEntry
	MAX-ACCESS not-accessible
	STATUS current
	DESCRIPTION
		"Columns in the ltmStreamProfileStat Table"
	INDEX {
		ltmStreamProfileStatName
	}
	::= { ltmStreamProfileStatTable 1 }

LtmStreamProfileStatEntry ::=
	SEQUENCE {
        	ltmStreamProfileStatName                                  LongDisplayString,
        	ltmStreamProfileStatReplaces                              Counter64
	}

ltmStreamProfileStatName OBJECT-TYPE
	SYNTAX LongDisplayString
	MAX-ACCESS read-only
	STATUS current
	DESCRIPTION
		"The name of a stream profile."
	::= { ltmStreamProfileStatEntry 1 }

ltmStreamProfileStatReplaces OBJECT-TYPE
	SYNTAX Counter64
	MAX-ACCESS read-only
	STATUS current
	DESCRIPTION
		"The number of replace operations completed."
	::= { ltmStreamProfileStatEntry 2 }

--==================================================================
-- Profile_tcp
--==================================================================
ltmTcpProfileNumber OBJECT-TYPE
	SYNTAX INTEGER
	MAX-ACCESS read-only
	STATUS current
	DESCRIPTION
		"The number of ltmTcpProfile entries in the table."
	::= { ltmTcpProfile 1 }

ltmTcpProfileTable OBJECT-TYPE
	SYNTAX SEQUENCE OF LtmTcpProfileEntry
	MAX-ACCESS not-accessible
	STATUS current
	DESCRIPTION
		"A table containing information of TCP profile."
	::= { ltmTcpProfile 2 }

ltmTcpProfileEntry OBJECT-TYPE
	SYNTAX  LtmTcpProfileEntry
	MAX-ACCESS not-accessible
	STATUS current
	DESCRIPTION
		"Columns in the ltmTcpProfile Table"
	INDEX {
		ltmTcpProfileName
	}
	::= { ltmTcpProfileTable 1 }

LtmTcpProfileEntry ::=
	SEQUENCE {
        	ltmTcpProfileName                                         LongDisplayString,
        	ltmTcpProfileConfigSource                                 INTEGER,
        	ltmTcpProfileDefaultName                                  LongDisplayString,
        	ltmTcpProfileResetOnTimeout                               INTEGER,
        	ltmTcpProfileTimeWaitRecycle                              INTEGER,
        	ltmTcpProfileDelayedAcks                                  INTEGER,
        	ltmTcpProfileProxyMss                                     INTEGER,
        	ltmTcpProfileProxyOptions                                 INTEGER,
        	ltmTcpProfileProxyBufferLow                               Gauge,
        	ltmTcpProfileProxyBufferHigh                              Gauge,
        	ltmTcpProfileIdleTimeout                                  Gauge,
        	ltmTcpProfileTimeWaitTimeout                              Gauge,
        	ltmTcpProfileFinWaitTimeout                               Gauge,
        	ltmTcpProfileCloseWaitTimeout                             Gauge,
        	ltmTcpProfileSndbuf                                       Gauge,
        	ltmTcpProfileRcvwnd                                       Gauge,
        	ltmTcpProfileKeepAliveInterval                            Gauge,
        	ltmTcpProfileSynMaxrtx                                    Gauge,
        	ltmTcpProfileMaxrtx                                       Gauge,
        	ltmTcpProfileIpTosToClient                                INTEGER,
        	ltmTcpProfileLinkQosToClient                              INTEGER,
        	ltmTcpProfileDeferredAccept                               INTEGER,
        	ltmTcpProfileSelectiveAcks                                INTEGER,
        	ltmTcpProfileEcn                                          INTEGER,
        	ltmTcpProfileLimitedTransmit                              INTEGER,
        	ltmTcpProfileHighPerfTcpExt                               INTEGER,
        	ltmTcpProfileSlowStart                                    INTEGER,
        	ltmTcpProfileBandwidthDelay                               INTEGER,
        	ltmTcpProfileNagle                                        INTEGER,
        	ltmTcpProfileAckOnPush                                    INTEGER,
        	ltmTcpProfileMd5Sig                                       INTEGER,
        	ltmTcpProfileMd5SigPass                                   LongDisplayString,
        	ltmTcpProfileAbc                                          INTEGER,
        	ltmTcpProfileCongestionCtrl                               INTEGER,
        	ltmTcpProfileDsack                                        INTEGER,
        	ltmTcpProfileCmetricsCache                                INTEGER,
        	ltmTcpProfileVerifiedAccept                               INTEGER,
        	ltmTcpProfilePktLossIgnoreRate                            Gauge,
        	ltmTcpProfilePktLossIgnoreBurst                           Gauge,
        	ltmTcpProfileZeroWindowTimeout                            Gauge,
        	ltmTcpProfileInitCwnd                                     Gauge,
        	ltmTcpProfileInitRwnd                                     Gauge,
        	ltmTcpProfileDelayWindowControl                           INTEGER,
        	ltmTcpProfileSynRtoBase                                   Gauge,
        	ltmTcpProfileTimestamps                                   INTEGER,
        	ltmTcpProfileMinRto                                       Gauge,
        	ltmTcpProfileMptcp                                        INTEGER,
        	ltmTcpProfileRatePace                                     INTEGER,
        	ltmTcpProfileMptcpCsum                                    INTEGER,
        	ltmTcpProfileMptcpCsumVerify                              INTEGER,
        	ltmTcpProfileMptcpDebug                                   INTEGER,
        	ltmTcpProfileMptcpFallback                                INTEGER,
        	ltmTcpProfileMptcpJoinmax                                 Gauge,
        	ltmTcpProfileMptcpNojoindssack                            INTEGER,
        	ltmTcpProfileMptcpRtomax                                  Gauge,
        	ltmTcpProfileMptcpRxmitmin                                Gauge,
        	ltmTcpProfileMptcpSubflowmax                              Gauge,
        	ltmTcpProfileMptcpMakeafterbreak                          INTEGER,
        	ltmTcpProfileMptcpTimeout                                 Gauge,
        	ltmTcpProfileMptcpFastjoin                                INTEGER,
        	ltmTcpProfileEarlyRetransmit                              INTEGER,
        	ltmTcpProfileTailLossProbe                                INTEGER,
        	ltmTcpProfileCmetricsCacheTimeout                         Gauge,
        	ltmTcpProfileRatePaceMaxRate                              Gauge,
        	ltmTcpProfileFastOpen                                     INTEGER,
        	ltmTcpProfileFastOpenCookieExpiration                     Gauge,
        	ltmTcpProfileFinWait2Timeout                              Gauge,
        	ltmTcpProfileRexmtThresh                                  Gauge,
        	ltmTcpProfileAutoSendBuffer                               INTEGER,
        	ltmTcpProfileAutoReceiveWindow                            INTEGER,
        	ltmTcpProfileAutoProxyBuffer                              INTEGER,
        	ltmTcpProfileEnhancedLossRecovery                         INTEGER,
        	ltmTcpProfilePushFlag                                     INTEGER
	}

ltmTcpProfileName OBJECT-TYPE
	SYNTAX LongDisplayString
	MAX-ACCESS read-only
	STATUS current
	DESCRIPTION
		"The name of a TCP profile."
	::= { ltmTcpProfileEntry 1 }

ltmTcpProfileConfigSource OBJECT-TYPE
	SYNTAX INTEGER {
		usercfg(0),
		basecfg(1)
	}
	MAX-ACCESS read-only
	STATUS current
	DESCRIPTION
		"The state that specifies whether this is a base/pre-configured profile
		or user defined profile."
	::= { ltmTcpProfileEntry 2 }

ltmTcpProfileDefaultName OBJECT-TYPE
	SYNTAX LongDisplayString
	MAX-ACCESS read-only
	STATUS current
	DESCRIPTION
		"The name of the profile from which the specified profile derives
		its attribute default values."
	::= { ltmTcpProfileEntry 3 }

ltmTcpProfileResetOnTimeout OBJECT-TYPE
	SYNTAX INTEGER {
		false(0),
		true(1)
	}
	MAX-ACCESS read-only
	STATUS current
	DESCRIPTION
		"The feature of reset for idle timeout.
		If true and a TCP connection exceeds its idle_timeout, send a reset
		in addition to deleting the connection."
	::= { ltmTcpProfileEntry 4 }

ltmTcpProfileTimeWaitRecycle OBJECT-TYPE
	SYNTAX INTEGER {
		false(0),
		true(1)
	}
	MAX-ACCESS read-only
	STATUS current
	DESCRIPTION
		"Recycle connection when SYN is received in TIME-WAIT state."
	::= { ltmTcpProfileEntry 5 }

ltmTcpProfileDelayedAcks OBJECT-TYPE
	SYNTAX INTEGER {
		false(0),
		true(1)
	}
	MAX-ACCESS read-only
	STATUS current
	DESCRIPTION
		"If true, Enable delayed ACK to allow coalescing of multiple ACK responses."
	::= { ltmTcpProfileEntry 6 }

ltmTcpProfileProxyMss OBJECT-TYPE
	SYNTAX INTEGER {
		false(0),
		true(1)
	}
	MAX-ACCESS read-only
	STATUS current
	DESCRIPTION
		"Whether or not to proxy maximum segment size.
		If true, advertise the same mss to the server as was
		negotiated with the client."
	::= { ltmTcpProfileEntry 7 }

ltmTcpProfileProxyOptions OBJECT-TYPE
	SYNTAX INTEGER {
		false(0),
		true(1)
	}
	MAX-ACCESS read-only
	STATUS current
	DESCRIPTION
		"Whether or not to proxy an option.
		If true, advertise an option (e.g. time-stamps) to
		the server only if it was negotiated with the client."
	::= { ltmTcpProfileEntry 8 }

ltmTcpProfileProxyBufferLow OBJECT-TYPE
	SYNTAX Gauge
	MAX-ACCESS read-only
	STATUS current
	DESCRIPTION
		"The proxy buffer level at which the receive window is opened."
	::= { ltmTcpProfileEntry 9 }

ltmTcpProfileProxyBufferHigh OBJECT-TYPE
	SYNTAX Gauge
	MAX-ACCESS read-only
	STATUS current
	DESCRIPTION
		"The proxy buffer level at which the receive window is closed."
	::= { ltmTcpProfileEntry 10 }

ltmTcpProfileIdleTimeout OBJECT-TYPE
	SYNTAX Gauge
	MAX-ACCESS read-only
	STATUS current
	DESCRIPTION
		"The number of seconds without traffic before a connection is
		eligible for deletion."
	::= { ltmTcpProfileEntry 11 }

ltmTcpProfileTimeWaitTimeout OBJECT-TYPE
	SYNTAX Gauge
	MAX-ACCESS read-only
	STATUS current
	DESCRIPTION
		"The milliseconds in TIME-WAIT before entering CLOSED state."
	::= { ltmTcpProfileEntry 12 }

ltmTcpProfileFinWaitTimeout OBJECT-TYPE
	SYNTAX Gauge
	MAX-ACCESS read-only
	STATUS current
	DESCRIPTION
		"The number of seconds to remain in FIN-WAIT-1 or CLOSING state
		before giving up. Zero is forever (or until maxrtx of FIN)."
	::= { ltmTcpProfileEntry 13 }

ltmTcpProfileCloseWaitTimeout OBJECT-TYPE
	SYNTAX Gauge
	MAX-ACCESS read-only
	STATUS current
	DESCRIPTION
		"The number of seconds to remain in LAST-ACK state before
		giving up. Zero is forever (or until maxrtx of FIN)."
	::= { ltmTcpProfileEntry 14 }

ltmTcpProfileSndbuf OBJECT-TYPE
	SYNTAX Gauge
	MAX-ACCESS read-only
	STATUS current
	DESCRIPTION
		"Send buffer size in bytes."
	::= { ltmTcpProfileEntry 15 }

ltmTcpProfileRcvwnd OBJECT-TYPE
	SYNTAX Gauge
	MAX-ACCESS read-only
	STATUS current
	DESCRIPTION
		"Receive window size in bytes."
	::= { ltmTcpProfileEntry 16 }

ltmTcpProfileKeepAliveInterval OBJECT-TYPE
	SYNTAX Gauge
	MAX-ACCESS read-only
	STATUS current
	DESCRIPTION
		"Keep alive probe interval in milliseconds."
	::= { ltmTcpProfileEntry 17 }

ltmTcpProfileSynMaxrtx OBJECT-TYPE
	SYNTAX Gauge
	MAX-ACCESS read-only
	STATUS current
	DESCRIPTION
		"The maximum number of retransmissions of SYN segments."
	::= { ltmTcpProfileEntry 18 }

ltmTcpProfileMaxrtx OBJECT-TYPE
	SYNTAX Gauge
	MAX-ACCESS read-only
	STATUS current
	DESCRIPTION
		"The maximum number of retransmissions of data segments."
	::= { ltmTcpProfileEntry 19 }

ltmTcpProfileIpTosToClient OBJECT-TYPE
	SYNTAX INTEGER
	MAX-ACCESS read-only
	STATUS current
	DESCRIPTION
		"The IP type of service set in packets sent to client. Default:None."
	::= { ltmTcpProfileEntry 20 }

ltmTcpProfileLinkQosToClient OBJECT-TYPE
	SYNTAX INTEGER
	MAX-ACCESS read-only
	STATUS current
	DESCRIPTION
		"The link quality of service set in packets sent to client. Default:None."
	::= { ltmTcpProfileEntry 21 }

ltmTcpProfileDeferredAccept OBJECT-TYPE
	SYNTAX INTEGER {
		false(0),
		true(1)
	}
	MAX-ACCESS read-only
	STATUS current
	DESCRIPTION
		"The state that if true, defers allocation of connection chain context
		until payload from client has been seen."
	::= { ltmTcpProfileEntry 22 }

ltmTcpProfileSelectiveAcks OBJECT-TYPE
	SYNTAX INTEGER {
		false(0),
		true(1)
	}
	MAX-ACCESS read-only
	STATUS current
	DESCRIPTION
		"The state that if true, enable RFC2018 Selective Acknowledgements."
	::= { ltmTcpProfileEntry 23 }

ltmTcpProfileEcn OBJECT-TYPE
	SYNTAX INTEGER {
		false(0),
		true(1)
	}
	MAX-ACCESS read-only
	STATUS current
	DESCRIPTION
		"The state that if true, enable RFC3168 Extended Congestion Notification (ECN)."
	::= { ltmTcpProfileEntry 24 }

ltmTcpProfileLimitedTransmit OBJECT-TYPE
	SYNTAX INTEGER {
		false(0),
		true(1)
	}
	MAX-ACCESS read-only
	STATUS current
	DESCRIPTION
		"The state that if true, enables support for RFC3042 Limited Transmit Recovery"
	::= { ltmTcpProfileEntry 25 }

ltmTcpProfileHighPerfTcpExt OBJECT-TYPE
	SYNTAX INTEGER {
		false(0),
		true(1)
	}
	MAX-ACCESS read-only
	STATUS	 deprecated
	DESCRIPTION
		"Deprecated! Replaced by ltmTcpProfileTimestamps.
		The state that if true, enables support for RFC1323 timestamps
		and window scaling (high bandwidth TCP extensions)."
	::= { ltmTcpProfileEntry 26 }

ltmTcpProfileSlowStart OBJECT-TYPE
	SYNTAX INTEGER {
		false(0),
		true(1)
	}
	MAX-ACCESS read-only
	STATUS current
	DESCRIPTION
		"The state if true, enable TCP slow-start by default. We use RFC3390 to
		slow-start rather than traditional congestion avoidance mechanisms."
	::= { ltmTcpProfileEntry 27 }

ltmTcpProfileBandwidthDelay OBJECT-TYPE
	SYNTAX INTEGER {
		false(0),
		true(1)
	}
	MAX-ACCESS read-only
	STATUS	 deprecated
	DESCRIPTION
		"Deprecated! The state if true, attempt to calculate the optimal bandwidth
	        to use to the peer based on throughput and round-trip time,
	        and don't exceed it."
	::= { ltmTcpProfileEntry 28 }

ltmTcpProfileNagle OBJECT-TYPE
	SYNTAX INTEGER {
		false(0),
		true(1),
		auto(2)
	}
	MAX-ACCESS read-only
	STATUS current
	DESCRIPTION
		"The state if true, delay sending data < MSS in size unless
	    all prior data has been ACKed. This leads to less in-flight small-data,
	    and less chance for drops, but can harm interactivity. When state is false,
	    sending data < MSS in size is not delayed. When state is auto, the use of
	    Nagle's algorithm is decided based on network conditions. Named after
	    Nagle's algorithm."
	::= { ltmTcpProfileEntry 29 }

ltmTcpProfileAckOnPush OBJECT-TYPE
	SYNTAX INTEGER {
		false(0),
		true(1)
	}
	MAX-ACCESS read-only
	STATUS current
	DESCRIPTION
		"The state if true, data-bearing in-order TCP segments will elicit
		immediate ACKs from us if they have the PUSH flag set, regardless of
		the setting of the delayed-ack profile option."
	::= { ltmTcpProfileEntry 30 }

ltmTcpProfileMd5Sig OBJECT-TYPE
	SYNTAX INTEGER {
		false(0),
		true(1)
	}
	MAX-ACCESS read-only
	STATUS current
	DESCRIPTION
		"The state if true, use RFC2385 TCP-MD5 signatures to protect
		TCP traffic against intermediate tampering."
	::= { ltmTcpProfileEntry 31 }

ltmTcpProfileMd5SigPass OBJECT-TYPE
	SYNTAX LongDisplayString
	MAX-ACCESS read-only
	STATUS	 deprecated
	DESCRIPTION
		"Deprecated! No longer supported.
	        This is a plaintext passphrase which may be between 1 and 80
	        characters in length, and is used in a shared-secret scheme
	        to implement the spoof-prevention parts of RFC2385."
	::= { ltmTcpProfileEntry 32 }

ltmTcpProfileAbc OBJECT-TYPE
	SYNTAX INTEGER {
		false(0),
		true(1)
	}
	MAX-ACCESS read-only
	STATUS current
	DESCRIPTION
		"The state that if it is true, count the number of bytes ACKed
		rather than the number of returning ACKs from the peer when
		in the linear congestion-window expansion phase of a TCP
		connection. This algorithm and its benefits are described
		in RFC3465 (Appropriate Byte Counting)."
	::= { ltmTcpProfileEntry 33 }

ltmTcpProfileCongestionCtrl OBJECT-TYPE
	SYNTAX INTEGER {
		reno(0),
		newreno(1),
		scalable(2),
		highspeed(3),
		none(4),
		vegas(5),
		illinois(6),
		woodside(7),
		chd(8),
		cdg(9),
		cubic(10),
		westwood(11),
		bbr(12)
	}
	MAX-ACCESS read-only
	STATUS current
	DESCRIPTION
		"The TCP congestion control mode, guiding cwnd growth.
		reno - RENO congestion control mode;
		newreno - new RENO congestion control mode;
		scalable - scalable congestion control mode. It will do MIMD
	   	           on cwnd besides NewReno retransmission;
		highspeed - high-speed congestion control mode, per RFC3649;
		none - no congestion control;
		vegas - vegas congestion control, delay-based;
		illinois - illinois congestion control, hybrid loss and delay;
		woodside - woodside congestion control, hybrid loss and delay;
		chd - chd congestion control, queue-delay based;
		cdg - cdg congestion control, RTT based;
		cubic - cubic congestion control, optimized for high latency,
		        high bandwidth connections;
		westwood - westwood+ congestion control, bandwidth estimation;
		bbr - bbr congestion control, bandwidth and RTT based."
	::= { ltmTcpProfileEntry 34 }

ltmTcpProfileDsack OBJECT-TYPE
	SYNTAX INTEGER {
		false(0),
		true(1)
	}
	MAX-ACCESS read-only
	STATUS current
	DESCRIPTION
		"The state that if true, enable support for RFC2883 D-SACK (Duplicate Selective Acknowledgment)."
	::= { ltmTcpProfileEntry 35 }

ltmTcpProfileCmetricsCache OBJECT-TYPE
	SYNTAX INTEGER {
		false(0),
		true(1)
	}
	MAX-ACCESS read-only
	STATUS current
	DESCRIPTION
		"The state that if true, use the routing table metrics cache to
		retrieve the last-known tcp congestion parameters.
		(Congestion window, round-trip-times, and slow-start threshold.)"
	::= { ltmTcpProfileEntry 36 }

ltmTcpProfileVerifiedAccept OBJECT-TYPE
	SYNTAX INTEGER {
		false(0),
		true(1)
	}
	MAX-ACCESS read-only
	STATUS current
	DESCRIPTION
		"The state that if true, the device must not respond to the clients
	         SYN with a SYN-ACK until it receives a SYN-ACK from
	         the server, indicating that the port is open."
	::= { ltmTcpProfileEntry 37 }

ltmTcpProfilePktLossIgnoreRate OBJECT-TYPE
	SYNTAX Gauge
	MAX-ACCESS read-only
	STATUS current
	DESCRIPTION
		"Specifies the threshold of packets lost per million at which the system should perform congestion control.
	         Measured in packets per million. Valid values are from 0 to 1000000."
	::= { ltmTcpProfileEntry 38 }

ltmTcpProfilePktLossIgnoreBurst OBJECT-TYPE
	SYNTAX Gauge
	MAX-ACCESS read-only
	STATUS current
	DESCRIPTION
		"Specifies the likelihood of performing congestion control when multiple packets in a row are lost even
	         if the loss threshold has not been exceeded. Valid values are from 0 to 32. Higher values decrease the
	         likelihood of performing congestion control."
	::= { ltmTcpProfileEntry 39 }

ltmTcpProfileZeroWindowTimeout OBJECT-TYPE
	SYNTAX Gauge
	MAX-ACCESS read-only
	STATUS current
	DESCRIPTION
		"Specifies the timeout in milliseconds for terminating a connection with an effective zero length TCP
		 transmit window. The timeout starts when the peer advertises a zero length TCP window or when enough
		 data has been sent to fill the previously advertised window. The timer is canceled when a non-zero
		 length window is received. The default is 20000 milliseconds."
	::= { ltmTcpProfileEntry 40 }

ltmTcpProfileInitCwnd OBJECT-TYPE
	SYNTAX Gauge
	MAX-ACCESS read-only
	STATUS current
	DESCRIPTION
		"Initial congestion window size for connections to this destination. Actual window size is this value
	         multiplied by the MSS (Maximal Segment Size) for same connection. The default is zero, meaning to
	         use the values specified in RFC2414. Allowed values are in the range of 0 to 64."
	::= { ltmTcpProfileEntry 41 }

ltmTcpProfileInitRwnd OBJECT-TYPE
	SYNTAX Gauge
	MAX-ACCESS read-only
	STATUS current
	DESCRIPTION
		"Initial receive window size for connections to this destination. The actual window size is this value
	         multiplied by the MSS (Maximal Segment Size) of the connection. The default value is zero, meaning
	         to use Slow Start value. Allowed values are in the range of 0 to 64."
	::= { ltmTcpProfileEntry 42 }

ltmTcpProfileDelayWindowControl OBJECT-TYPE
	SYNTAX INTEGER {
		false(0),
		true(1)
	}
	MAX-ACCESS read-only
	STATUS current
	DESCRIPTION
		"If enabled, uses an estimate of queuing delay as a measure of congestion to control, in addition to
	         the normal loss based control, the amount of data sent."
	::= { ltmTcpProfileEntry 43 }

ltmTcpProfileSynRtoBase OBJECT-TYPE
	SYNTAX Gauge
	MAX-ACCESS read-only
	STATUS current
	DESCRIPTION
		"Initial RTO (Retransmission TimeOut) base multiplier for SYN retransmission, specified in milliseconds.
	         This value is modified by the exponential backoff table to select the interval for subsequent
	         retransmissions."
	::= { ltmTcpProfileEntry 44 }

ltmTcpProfileTimestamps OBJECT-TYPE
	SYNTAX INTEGER {
		false(0),
		true(1)
	}
	MAX-ACCESS read-only
	STATUS current
	DESCRIPTION
		"The state that if true, enables support for RFC1323 timestamps (high bandwidth TCP extension)."
	::= { ltmTcpProfileEntry 45 }

ltmTcpProfileMinRto OBJECT-TYPE
	SYNTAX Gauge
	MAX-ACCESS read-only
	STATUS current
	DESCRIPTION
		"Specifies the minimum TCP retransmission timeout in milliseconds. The timeout starts when the sender sends
	         a packet containing data. The timer is canceled when all outstanding data has been acknowledged. The timer
	         restarts when an ACK is received to acknowledge new data. The default is 0 milliseconds; which means using
	         the TCP stack default. Maximum value is 5000 milliseconds."
	::= { ltmTcpProfileEntry 46 }

ltmTcpProfileMptcp OBJECT-TYPE
	SYNTAX INTEGER {
		disabled(0),
		enabled(1),
		passthrough(2)
	}
	MAX-ACCESS read-only
	STATUS current
	DESCRIPTION
		"The state that, if enabled, all incoming flows handle by the MPTCP stack allowing for support of multipath
	     enabled connections. When passthrough, MPTCP flows are not terminated by this virtual."
	::= { ltmTcpProfileEntry 47 }

ltmTcpProfileRatePace OBJECT-TYPE
	SYNTAX INTEGER {
		false(0),
		true(1)
	}
	MAX-ACCESS read-only
	STATUS current
	DESCRIPTION
		"The state that, when true, enables pacing of data transmission."
	::= { ltmTcpProfileEntry 48 }

ltmTcpProfileMptcpCsum OBJECT-TYPE
	SYNTAX INTEGER {
		false(0),
		true(1)
	}
	MAX-ACCESS read-only
	STATUS current
	DESCRIPTION
		"The state that, when true, enabled checksums support by this MPTCP enabled device."
	::= { ltmTcpProfileEntry 49 }

ltmTcpProfileMptcpCsumVerify OBJECT-TYPE
	SYNTAX INTEGER {
		false(0),
		true(1)
	}
	MAX-ACCESS read-only
	STATUS current
	DESCRIPTION
		"The state that, when true, enables verifying incoming checksums, and checksum failure causes
	                    connection abort."
	::= { ltmTcpProfileEntry 50 }

ltmTcpProfileMptcpDebug OBJECT-TYPE
	SYNTAX INTEGER {
		false(0),
		true(1)
	}
	MAX-ACCESS read-only
	STATUS current
	DESCRIPTION
		"The state that, when true, enables debug logging and statistics for MPTCP."
	::= { ltmTcpProfileEntry 51 }

ltmTcpProfileMptcpFallback OBJECT-TYPE
	SYNTAX INTEGER {
		reset(0),
		retransmit(1),
		activeaccept(2),
		accept(3)
	}
	MAX-ACCESS read-only
	STATUS current
	DESCRIPTION
		"The MPTCP fallback control mode,
	    reboot - reboot control mode;
	    retransmit - retransmit control mode;
	    activeaccept - activeaccept control mode;
	    accept - accept control mode."
	::= { ltmTcpProfileEntry 52 }

ltmTcpProfileMptcpJoinmax OBJECT-TYPE
	SYNTAX Gauge
	MAX-ACCESS read-only
	STATUS current
	DESCRIPTION
		"Specifies the maximum number of simultaneous join attempts on a given flow. Default value is 5. Maximum value is 20."
	::= { ltmTcpProfileEntry 53 }

ltmTcpProfileMptcpNojoindssack OBJECT-TYPE
	SYNTAX INTEGER {
		false(0),
		true(1)
	}
	MAX-ACCESS read-only
	STATUS current
	DESCRIPTION
		"The state that, when true, the no DSS option is sent on the JOIN ACK."
	::= { ltmTcpProfileEntry 54 }

ltmTcpProfileMptcpRtomax OBJECT-TYPE
	SYNTAX Gauge
	MAX-ACCESS read-only
	STATUS current
	DESCRIPTION
		"Specifies the the number of RTOs before declaring subflow dead. Default value is 5. Maximum value is 12. Minimum value is 3."
	::= { ltmTcpProfileEntry 55 }

ltmTcpProfileMptcpRxmitmin OBJECT-TYPE
	SYNTAX Gauge
	MAX-ACCESS read-only
	STATUS current
	DESCRIPTION
		"Specifies the minimum value (in milliseconds) of retransmission timer for these MPTCP flows. Default value is 1000. Maximum value is 5000. Minimum value is 200."
	::= { ltmTcpProfileEntry 56 }

ltmTcpProfileMptcpSubflowmax OBJECT-TYPE
	SYNTAX Gauge
	MAX-ACCESS read-only
	STATUS current
	DESCRIPTION
		"Specifies the maximum number of MPTCP subflows for a single flow. Default value is 6. Maximum value is 10."
	::= { ltmTcpProfileEntry 57 }

ltmTcpProfileMptcpMakeafterbreak OBJECT-TYPE
	SYNTAX INTEGER {
		false(0),
		true(1)
	}
	MAX-ACCESS read-only
	STATUS current
	DESCRIPTION
		"The state that, when true, causes after break functionality allowing for Long-Lived MPTCP sessions."
	::= { ltmTcpProfileEntry 58 }

ltmTcpProfileMptcpTimeout OBJECT-TYPE
	SYNTAX Gauge
	MAX-ACCESS read-only
	STATUS current
	DESCRIPTION
		"Specifies the timeout value to discard long-lived sessions that do not have an active flow. Default value is 3600 sec. Maximum value is 36000 sec."
	::= { ltmTcpProfileEntry 59 }

ltmTcpProfileMptcpFastjoin OBJECT-TYPE
	SYNTAX INTEGER {
		false(0),
		true(1)
	}
	MAX-ACCESS read-only
	STATUS current
	DESCRIPTION
		"The state that, when true, enables FAST join, allowing data to be sent on the MP_JOIN SYN, which can allow a server response to occur in parallel with the JOIN"
	::= { ltmTcpProfileEntry 60 }

ltmTcpProfileEarlyRetransmit OBJECT-TYPE
	SYNTAX INTEGER {
		false(0),
		true(1)
	}
	MAX-ACCESS read-only
	STATUS current
	DESCRIPTION
		"The state that if true, enables support for RFC5827 Early Retransmit"
	::= { ltmTcpProfileEntry 61 }

ltmTcpProfileTailLossProbe OBJECT-TYPE
	SYNTAX INTEGER {
		false(0),
		true(1)
	}
	MAX-ACCESS read-only
	STATUS current
	DESCRIPTION
		"The state that if true, enables support for Tail Loss Probe"
	::= { ltmTcpProfileEntry 62 }

ltmTcpProfileCmetricsCacheTimeout OBJECT-TYPE
	SYNTAX Gauge
	MAX-ACCESS read-only
	STATUS current
	DESCRIPTION
		"Specifies the time, in seconds, for which entries in the congestion
	        metrics cache are valid. The default value is 0, which defers to
	        the sys db variable route.metrics.timeout. Valid values are from 0 to
	        1000000."
	::= { ltmTcpProfileEntry 63 }

ltmTcpProfileRatePaceMaxRate OBJECT-TYPE
	SYNTAX Gauge
	MAX-ACCESS read-only
	STATUS current
	DESCRIPTION
		"Specifies the maximum rate, in bytes per second, at which the rate
	        pacing feature may transmit data.  The default value is 0, which
	        means no maximum rate is enforced."
	::= { ltmTcpProfileEntry 64 }

ltmTcpProfileFastOpen OBJECT-TYPE
	SYNTAX INTEGER {
		false(0),
		true(1)
	}
	MAX-ACCESS read-only
	STATUS current
	DESCRIPTION
		"The state that if true, enables support for Fast Open."
	::= { ltmTcpProfileEntry 65 }

ltmTcpProfileFastOpenCookieExpiration OBJECT-TYPE
	SYNTAX Gauge
	MAX-ACCESS read-only
	STATUS current
	DESCRIPTION
		"Specifies the number of seconds a Fast Open Cookie provided by a BIG-IP is valid for incoming SYN packets from that client. The default value is 21600 (6 hours). The range is from 0 (meaning use the default) to 1000000."
	::= { ltmTcpProfileEntry 66 }

ltmTcpProfileFinWait2Timeout OBJECT-TYPE
	SYNTAX Gauge
	MAX-ACCESS read-only
	STATUS current
	DESCRIPTION
		"The number of seconds to remain in FIN-WAIT-2 state before giving up.
		Zero is forever (or until maxrtx of FIN)."
	::= { ltmTcpProfileEntry 67 }

ltmTcpProfileRexmtThresh OBJECT-TYPE
	SYNTAX Gauge
	MAX-ACCESS read-only
	STATUS current
	DESCRIPTION
		"Specifies the number of duplicate ACKs received (retransmit threshold) before starting fast recovery. Default value is 3. The range is from 3 to 255."
	::= { ltmTcpProfileEntry 68 }

ltmTcpProfileAutoSendBuffer OBJECT-TYPE
	SYNTAX INTEGER {
		false(0),
		true(1)
	}
	MAX-ACCESS read-only
	STATUS current
	DESCRIPTION
		"The state that if true, enables support for send buffer auto-tuning."
	::= { ltmTcpProfileEntry 69 }

ltmTcpProfileAutoReceiveWindow OBJECT-TYPE
	SYNTAX INTEGER {
		false(0),
		true(1)
	}
	MAX-ACCESS read-only
	STATUS current
	DESCRIPTION
		"The state that if true, enables support for receive window auto-tuning."
	::= { ltmTcpProfileEntry 70 }

ltmTcpProfileAutoProxyBuffer OBJECT-TYPE
	SYNTAX INTEGER {
		false(0),
		true(1)
	}
	MAX-ACCESS read-only
	STATUS current
	DESCRIPTION
		"The state that if true, enables support for proxy buffer auto-tuning."
	::= { ltmTcpProfileEntry 71 }

ltmTcpProfileEnhancedLossRecovery OBJECT-TYPE
	SYNTAX INTEGER {
		false(0),
		true(1)
	}
	MAX-ACCESS read-only
	STATUS current
	DESCRIPTION
		"The state that if true, enables support for Enhanced Loss Recovery"
	::= { ltmTcpProfileEntry 72 }

ltmTcpProfilePushFlag OBJECT-TYPE
	SYNTAX INTEGER {
		default(0),
		none(1),
		one(2),
		auto(3)
	}
	MAX-ACCESS read-only
	STATUS current
	DESCRIPTION
		"The TCP PUSH flag control mode, guiding sending PUSH segments.
		default - Default behavior mode;
		none - Do not send any PUSH flags mode;
		one - Send a PUSH flag with FIN segments mode;
		auto - Auto (send PUSH segments based on app/network conditions) mode"
	::= { ltmTcpProfileEntry 73 }

--==================================================================
-- Profile_tcp_stat
--==================================================================
ltmTcpProfileStatResetStats OBJECT-TYPE
	SYNTAX INTEGER
	MAX-ACCESS read-write
	STATUS current
	DESCRIPTION
		"The action to reset resettable statistics data in ltmTcpProfileStat.
		 Setting this value to 1 will reset statistics data.
		 Note, some statistics data may not be reset including data that are incremental counters."
	::= { ltmTcpProfileStat 1 }

ltmTcpProfileStatNumber OBJECT-TYPE
	SYNTAX INTEGER
	MAX-ACCESS read-only
	STATUS current
	DESCRIPTION
		"The number of ltmTcpProfileStat entries in the table."
	::= { ltmTcpProfileStat 2 }

ltmTcpProfileStatTable OBJECT-TYPE
	SYNTAX SEQUENCE OF LtmTcpProfileStatEntry
	MAX-ACCESS not-accessible
	STATUS current
	DESCRIPTION
		"A table containing statistic information of TCP profile."
	::= { ltmTcpProfileStat 3 }

ltmTcpProfileStatEntry OBJECT-TYPE
	SYNTAX  LtmTcpProfileStatEntry
	MAX-ACCESS not-accessible
	STATUS current
	DESCRIPTION
		"Columns in the ltmTcpProfileStat Table"
	INDEX {
		ltmTcpProfileStatName
	}
	::= { ltmTcpProfileStatTable 1 }

LtmTcpProfileStatEntry ::=
	SEQUENCE {
        	ltmTcpProfileStatName                                     LongDisplayString,
        	ltmTcpProfileStatOpen                                     Gauge,
        	ltmTcpProfileStatCloseWait                                Gauge,
        	ltmTcpProfileStatFinWait                                  Gauge,
        	ltmTcpProfileStatTimeWait                                 Gauge,
        	ltmTcpProfileStatAccepts                                  Counter64,
        	ltmTcpProfileStatAcceptfails                              Counter64,
        	ltmTcpProfileStatConnects                                 Counter64,
        	ltmTcpProfileStatConnfails                                Counter64,
        	ltmTcpProfileStatExpires                                  Counter64,
        	ltmTcpProfileStatAbandons                                 Counter64,
        	ltmTcpProfileStatRxrst                                    Counter64,
        	ltmTcpProfileStatRxbadsum                                 Counter64,
        	ltmTcpProfileStatRxbadseg                                 Counter64,
        	ltmTcpProfileStatRxooseg                                  Counter64,
        	ltmTcpProfileStatRxcookie                                 Counter64,
        	ltmTcpProfileStatRxbadcookie                              Counter64,
        	ltmTcpProfileStatSyncacheover                             Counter64,
        	ltmTcpProfileStatTxrexmits                                Counter64,
        	ltmTcpProfileStatFinWait2                                 Gauge
	}

ltmTcpProfileStatName OBJECT-TYPE
	SYNTAX LongDisplayString
	MAX-ACCESS read-only
	STATUS current
	DESCRIPTION
		"The name of a TCP profile."
	::= { ltmTcpProfileStatEntry 1 }

ltmTcpProfileStatOpen OBJECT-TYPE
	SYNTAX Gauge
	MAX-ACCESS read-only
	STATUS current
	DESCRIPTION
		"The number of current open connections."
	::= { ltmTcpProfileStatEntry 2 }

ltmTcpProfileStatCloseWait OBJECT-TYPE
	SYNTAX Gauge
	MAX-ACCESS read-only
	STATUS current
	DESCRIPTION
		"The number of current connections in CLOSE-WAIT/LAST-ACK."
	::= { ltmTcpProfileStatEntry 3 }

ltmTcpProfileStatFinWait OBJECT-TYPE
	SYNTAX Gauge
	MAX-ACCESS read-only
	STATUS current
	DESCRIPTION
		"The number of current connections in FIN-WAIT-1/CLOSING."
	::= { ltmTcpProfileStatEntry 4 }

ltmTcpProfileStatTimeWait OBJECT-TYPE
	SYNTAX Gauge
	MAX-ACCESS read-only
	STATUS current
	DESCRIPTION
		"The number of current connections in TIME-WAIT."
	::= { ltmTcpProfileStatEntry 5 }

ltmTcpProfileStatAccepts OBJECT-TYPE
	SYNTAX Counter64
	MAX-ACCESS read-only
	STATUS current
	DESCRIPTION
		"The number of connections accepted."
	::= { ltmTcpProfileStatEntry 6 }

ltmTcpProfileStatAcceptfails OBJECT-TYPE
	SYNTAX Counter64
	MAX-ACCESS read-only
	STATUS current
	DESCRIPTION
		"The number of connections not accepted."
	::= { ltmTcpProfileStatEntry 7 }

ltmTcpProfileStatConnects OBJECT-TYPE
	SYNTAX Counter64
	MAX-ACCESS read-only
	STATUS current
	DESCRIPTION
		"The number of connections established."
	::= { ltmTcpProfileStatEntry 8 }

ltmTcpProfileStatConnfails OBJECT-TYPE
	SYNTAX Counter64
	MAX-ACCESS read-only
	STATUS current
	DESCRIPTION
		"The number of connections failures."
	::= { ltmTcpProfileStatEntry 9 }

ltmTcpProfileStatExpires OBJECT-TYPE
	SYNTAX Counter64
	MAX-ACCESS read-only
	STATUS current
	DESCRIPTION
		"The number of connections expired due to idle timeout."
	::= { ltmTcpProfileStatEntry 10 }

ltmTcpProfileStatAbandons OBJECT-TYPE
	SYNTAX Counter64
	MAX-ACCESS read-only
	STATUS current
	DESCRIPTION
		"The number of connections abandoned connections due to
		retries/keep-alives."
	::= { ltmTcpProfileStatEntry 11 }

ltmTcpProfileStatRxrst OBJECT-TYPE
	SYNTAX Counter64
	MAX-ACCESS read-only
	STATUS current
	DESCRIPTION
		"The number of received RST."
	::= { ltmTcpProfileStatEntry 12 }

ltmTcpProfileStatRxbadsum OBJECT-TYPE
	SYNTAX Counter64
	MAX-ACCESS read-only
	STATUS current
	DESCRIPTION
		"The number of bad checksum."
	::= { ltmTcpProfileStatEntry 13 }

ltmTcpProfileStatRxbadseg OBJECT-TYPE
	SYNTAX Counter64
	MAX-ACCESS read-only
	STATUS current
	DESCRIPTION
		"The number of malformed segments."
	::= { ltmTcpProfileStatEntry 14 }

ltmTcpProfileStatRxooseg OBJECT-TYPE
	SYNTAX Counter64
	MAX-ACCESS read-only
	STATUS current
	DESCRIPTION
		"The number of out of order segments."
	::= { ltmTcpProfileStatEntry 15 }

ltmTcpProfileStatRxcookie OBJECT-TYPE
	SYNTAX Counter64
	MAX-ACCESS read-only
	STATUS current
	DESCRIPTION
		"The number of received SYN-cookies."
	::= { ltmTcpProfileStatEntry 16 }

ltmTcpProfileStatRxbadcookie OBJECT-TYPE
	SYNTAX Counter64
	MAX-ACCESS read-only
	STATUS current
	DESCRIPTION
		"The number of bad SYN-cookies."
	::= { ltmTcpProfileStatEntry 17 }

ltmTcpProfileStatSyncacheover OBJECT-TYPE
	SYNTAX Counter64
	MAX-ACCESS read-only
	STATUS current
	DESCRIPTION
		"The number of SYN-cache overflow."
	::= { ltmTcpProfileStatEntry 18 }

ltmTcpProfileStatTxrexmits OBJECT-TYPE
	SYNTAX Counter64
	MAX-ACCESS read-only
	STATUS current
	DESCRIPTION
		"The number of retransmitted segments."
	::= { ltmTcpProfileStatEntry 19 }

ltmTcpProfileStatFinWait2 OBJECT-TYPE
	SYNTAX Gauge
	MAX-ACCESS read-only
	STATUS current
	DESCRIPTION
		"The number of current connections in FIN-WAIT-2."
	::= { ltmTcpProfileStatEntry 20 }

--==================================================================
-- Profile_udp
--==================================================================
ltmUdpProfileNumber OBJECT-TYPE
	SYNTAX INTEGER
	MAX-ACCESS read-only
	STATUS current
	DESCRIPTION
		"The number of ltmUdpProfile entries in the table."
	::= { ltmUdpProfile 1 }

ltmUdpProfileTable OBJECT-TYPE
	SYNTAX SEQUENCE OF LtmUdpProfileEntry
	MAX-ACCESS not-accessible
	STATUS current
	DESCRIPTION
		"A table containing information of UDP profile."
	::= { ltmUdpProfile 2 }

ltmUdpProfileEntry OBJECT-TYPE
	SYNTAX  LtmUdpProfileEntry
	MAX-ACCESS not-accessible
	STATUS current
	DESCRIPTION
		"Columns in the ltmUdpProfile Table"
	INDEX {
		ltmUdpProfileName
	}
	::= { ltmUdpProfileTable 1 }

LtmUdpProfileEntry ::=
	SEQUENCE {
        	ltmUdpProfileName                                         LongDisplayString,
        	ltmUdpProfileConfigSource                                 INTEGER,
        	ltmUdpProfileDefaultName                                  LongDisplayString,
        	ltmUdpProfileIdleTimeout                                  Gauge,
        	ltmUdpProfileIpTosToClient                                INTEGER,
        	ltmUdpProfileLinkQosToClient                              INTEGER,
        	ltmUdpProfileDatagramLb                                   INTEGER,
        	ltmUdpProfileAllowNoPayload                               INTEGER,
        	ltmUdpProfileSndbuf                                       Gauge
	}

ltmUdpProfileName OBJECT-TYPE
	SYNTAX LongDisplayString
	MAX-ACCESS read-only
	STATUS current
	DESCRIPTION
		"The name of a UDP profile."
	::= { ltmUdpProfileEntry 1 }

ltmUdpProfileConfigSource OBJECT-TYPE
	SYNTAX INTEGER {
		usercfg(0),
		basecfg(1)
	}
	MAX-ACCESS read-only
	STATUS current
	DESCRIPTION
		"The state that specifies whether this is a base/pre-configured profile
		or user defined profile."
	::= { ltmUdpProfileEntry 2 }

ltmUdpProfileDefaultName OBJECT-TYPE
	SYNTAX LongDisplayString
	MAX-ACCESS read-only
	STATUS current
	DESCRIPTION
		"The name of the profile from which the specified profile derives
		its attribute default values."
	::= { ltmUdpProfileEntry 3 }

ltmUdpProfileIdleTimeout OBJECT-TYPE
	SYNTAX Gauge
	MAX-ACCESS read-only
	STATUS current
	DESCRIPTION
		"The umber of seconds without traffic before a flow is
		eligible for deletion."
	::= { ltmUdpProfileEntry 4 }

ltmUdpProfileIpTosToClient OBJECT-TYPE
	SYNTAX INTEGER
	MAX-ACCESS read-only
	STATUS current
	DESCRIPTION
		"The IP type of service set in packets sent to client. Default:None."
	::= { ltmUdpProfileEntry 5 }

ltmUdpProfileLinkQosToClient OBJECT-TYPE
	SYNTAX INTEGER
	MAX-ACCESS read-only
	STATUS current
	DESCRIPTION
		"The link quality of service set in packets sent to client. Default:None."
	::= { ltmUdpProfileEntry 6 }

ltmUdpProfileDatagramLb OBJECT-TYPE
	SYNTAX INTEGER {
		false(0),
		true(1)
	}
	MAX-ACCESS read-only
	STATUS current
	DESCRIPTION
		"The state indicating whether or not to load balance each UDP datagram separately."
	::= { ltmUdpProfileEntry 7 }

ltmUdpProfileAllowNoPayload OBJECT-TYPE
	SYNTAX INTEGER {
		false(0),
		true(1)
	}
	MAX-ACCESS read-only
	STATUS current
	DESCRIPTION
		"The state indicating whether to not allow the passage of datagrams with no payload."
	::= { ltmUdpProfileEntry 8 }

ltmUdpProfileSndbuf OBJECT-TYPE
	SYNTAX Gauge
	MAX-ACCESS read-only
	STATUS current
	DESCRIPTION
		"The send buffer size in bytes."
	::= { ltmUdpProfileEntry 9 }

--==================================================================
-- Profile_udp_stat
--==================================================================
ltmUdpProfileStatResetStats OBJECT-TYPE
	SYNTAX INTEGER
	MAX-ACCESS read-write
	STATUS current
	DESCRIPTION
		"The action to reset resettable statistics data in ltmUdpProfileStat.
		 Setting this value to 1 will reset statistics data.
		 Note, some statistics data may not be reset including data that are incremental counters."
	::= { ltmUdpProfileStat 1 }

ltmUdpProfileStatNumber OBJECT-TYPE
	SYNTAX INTEGER
	MAX-ACCESS read-only
	STATUS current
	DESCRIPTION
		"The number of ltmUdpProfileStat entries in the table."
	::= { ltmUdpProfileStat 2 }

ltmUdpProfileStatTable OBJECT-TYPE
	SYNTAX SEQUENCE OF LtmUdpProfileStatEntry
	MAX-ACCESS not-accessible
	STATUS current
	DESCRIPTION
		"A table containing information of UDP profile."
	::= { ltmUdpProfileStat 3 }

ltmUdpProfileStatEntry OBJECT-TYPE
	SYNTAX  LtmUdpProfileStatEntry
	MAX-ACCESS not-accessible
	STATUS current
	DESCRIPTION
		"Columns in the ltmUdpProfileStat Table"
	INDEX {
		ltmUdpProfileStatName
	}
	::= { ltmUdpProfileStatTable 1 }

LtmUdpProfileStatEntry ::=
	SEQUENCE {
        	ltmUdpProfileStatName                                     LongDisplayString,
        	ltmUdpProfileStatOpen                                     Gauge,
        	ltmUdpProfileStatAccepts                                  Counter64,
        	ltmUdpProfileStatAcceptfails                              Counter64,
        	ltmUdpProfileStatConnects                                 Counter64,
        	ltmUdpProfileStatConnfails                                Counter64,
        	ltmUdpProfileStatExpires                                  Counter64,
        	ltmUdpProfileStatRxdgram                                  Counter64,
        	ltmUdpProfileStatRxbaddgram                               Counter64,
        	ltmUdpProfileStatRxunreach                                Counter64,
        	ltmUdpProfileStatRxbadsum                                 Counter64,
        	ltmUdpProfileStatRxnosum                                  Counter64,
        	ltmUdpProfileStatTxdgram                                  Counter64
	}

ltmUdpProfileStatName OBJECT-TYPE
	SYNTAX LongDisplayString
	MAX-ACCESS read-only
	STATUS current
	DESCRIPTION
		"The name of a UDP profile."
	::= { ltmUdpProfileStatEntry 1 }

ltmUdpProfileStatOpen OBJECT-TYPE
	SYNTAX Gauge
	MAX-ACCESS read-only
	STATUS current
	DESCRIPTION
		"The number of current open connections."
	::= { ltmUdpProfileStatEntry 2 }

ltmUdpProfileStatAccepts OBJECT-TYPE
	SYNTAX Counter64
	MAX-ACCESS read-only
	STATUS current
	DESCRIPTION
		"The number of connections accepted."
	::= { ltmUdpProfileStatEntry 3 }

ltmUdpProfileStatAcceptfails OBJECT-TYPE
	SYNTAX Counter64
	MAX-ACCESS read-only
	STATUS current
	DESCRIPTION
		"The number of connections not accepted."
	::= { ltmUdpProfileStatEntry 4 }

ltmUdpProfileStatConnects OBJECT-TYPE
	SYNTAX Counter64
	MAX-ACCESS read-only
	STATUS current
	DESCRIPTION
		"The number of connections established."
	::= { ltmUdpProfileStatEntry 5 }

ltmUdpProfileStatConnfails OBJECT-TYPE
	SYNTAX Counter64
	MAX-ACCESS read-only
	STATUS current
	DESCRIPTION
		"The number of connections failures."
	::= { ltmUdpProfileStatEntry 6 }

ltmUdpProfileStatExpires OBJECT-TYPE
	SYNTAX Counter64
	MAX-ACCESS read-only
	STATUS current
	DESCRIPTION
		"The number of connections expired due to idle timeout."
	::= { ltmUdpProfileStatEntry 7 }

ltmUdpProfileStatRxdgram OBJECT-TYPE
	SYNTAX Counter64
	MAX-ACCESS read-only
	STATUS current
	DESCRIPTION
		"The number of received datagrams."
	::= { ltmUdpProfileStatEntry 8 }

ltmUdpProfileStatRxbaddgram OBJECT-TYPE
	SYNTAX Counter64
	MAX-ACCESS read-only
	STATUS current
	DESCRIPTION
		"The number of malformed datagrams."
	::= { ltmUdpProfileStatEntry 9 }

ltmUdpProfileStatRxunreach OBJECT-TYPE
	SYNTAX Counter64
	MAX-ACCESS read-only
	STATUS current
	DESCRIPTION
		"The number of received ICMP un-reached."
	::= { ltmUdpProfileStatEntry 10 }

ltmUdpProfileStatRxbadsum OBJECT-TYPE
	SYNTAX Counter64
	MAX-ACCESS read-only
	STATUS current
	DESCRIPTION
		"The number of bad checksum."
	::= { ltmUdpProfileStatEntry 11 }

ltmUdpProfileStatRxnosum OBJECT-TYPE
	SYNTAX Counter64
	MAX-ACCESS read-only
	STATUS current
	DESCRIPTION
		"The number of no checksum."
	::= { ltmUdpProfileStatEntry 12 }

ltmUdpProfileStatTxdgram OBJECT-TYPE
	SYNTAX Counter64
	MAX-ACCESS read-only
	STATUS current
	DESCRIPTION
		"The number of transmitted datagrams."
	::= { ltmUdpProfileStatEntry 13 }

--==================================================================
-- Rule
--==================================================================
ltmRuleNumber OBJECT-TYPE
	SYNTAX INTEGER
	MAX-ACCESS read-only
	STATUS current
	DESCRIPTION
		"The number of ltmRule entries in the table."
	::= { ltmRule 1 }

ltmRuleTable OBJECT-TYPE
	SYNTAX SEQUENCE OF LtmRuleEntry
	MAX-ACCESS not-accessible
	STATUS current
	DESCRIPTION
		"A table containing information of rules."
	::= { ltmRule 2 }

ltmRuleEntry OBJECT-TYPE
	SYNTAX  LtmRuleEntry
	MAX-ACCESS not-accessible
	STATUS current
	DESCRIPTION
		"Columns in the ltmRule Table"
	INDEX {
		ltmRuleName
	}
	::= { ltmRuleTable 1 }

LtmRuleEntry ::=
	SEQUENCE {
        	ltmRuleName                                               LongDisplayString,
        	ltmRuleDefinition                                         LongDisplayString,
        	ltmRuleConfigSource                                       INTEGER
	}

ltmRuleName OBJECT-TYPE
	SYNTAX LongDisplayString
	MAX-ACCESS read-only
	STATUS current
	DESCRIPTION
		"The name of a rule."
	::= { ltmRuleEntry 1 }

ltmRuleDefinition OBJECT-TYPE
	SYNTAX LongDisplayString
	MAX-ACCESS read-only
	STATUS	 deprecated
	DESCRIPTION
		"Deprecated!
		The definition of the specified rule."
	::= { ltmRuleEntry 2 }

ltmRuleConfigSource OBJECT-TYPE
	SYNTAX INTEGER {
		usercfg(0),
		basecfg(1)
	}
	MAX-ACCESS read-only
	STATUS current
	DESCRIPTION
		"The type of rule that the specified rule is associating with.
		It is either a base/pre-configured rule or user defined rule."
	::= { ltmRuleEntry 3 }

--==================================================================
-- Rule_event
--==================================================================
ltmRuleEventNumber OBJECT-TYPE
	SYNTAX INTEGER
	MAX-ACCESS read-only
	STATUS current
	DESCRIPTION
		"The number of ltmRuleEvent entries in the table."
	::= { ltmRuleEvent 1 }

ltmRuleEventTable OBJECT-TYPE
	SYNTAX SEQUENCE OF LtmRuleEventEntry
	MAX-ACCESS not-accessible
	STATUS current
	DESCRIPTION
		"A table containing information of rule events."
	::= { ltmRuleEvent 2 }

ltmRuleEventEntry OBJECT-TYPE
	SYNTAX  LtmRuleEventEntry
	MAX-ACCESS not-accessible
	STATUS current
	DESCRIPTION
		"Columns in the ltmRuleEvent Table"
	INDEX {
		ltmRuleEventName,
		ltmRuleEventEventType,
		ltmRuleEventPriority
	}
	::= { ltmRuleEventTable 1 }

LtmRuleEventEntry ::=
	SEQUENCE {
        	ltmRuleEventName                                          LongDisplayString,
        	ltmRuleEventEventType                                     LongDisplayString,
        	ltmRuleEventPriority                                      INTEGER,
        	ltmRuleEventScript                                        LongDisplayString
	}

ltmRuleEventName OBJECT-TYPE
	SYNTAX LongDisplayString
	MAX-ACCESS read-only
	STATUS current
	DESCRIPTION
		"The name of a rule."
	::= { ltmRuleEventEntry 1 }

ltmRuleEventEventType OBJECT-TYPE
	SYNTAX LongDisplayString
	MAX-ACCESS read-only
	STATUS current
	DESCRIPTION
		"The event type which the rule is used for."
	::= { ltmRuleEventEntry 2 }

ltmRuleEventPriority OBJECT-TYPE
	SYNTAX INTEGER(0..32767)
	MAX-ACCESS read-only
	STATUS current
	DESCRIPTION
		"The execution priority of this rule event."
	::= { ltmRuleEventEntry 3 }

ltmRuleEventScript OBJECT-TYPE
	SYNTAX LongDisplayString
	MAX-ACCESS read-only
	STATUS	 deprecated
	DESCRIPTION
		"Deprecated!.
	        The TCL script for this rule event."
	::= { ltmRuleEventEntry 4 }

--==================================================================
-- Rule_stat
--==================================================================
ltmRuleEventStatResetStats OBJECT-TYPE
	SYNTAX INTEGER
	MAX-ACCESS read-write
	STATUS current
	DESCRIPTION
		"The action to reset resettable statistics data in ltmRuleEventStat.
		 Setting this value to 1 will reset statistics data.
		 Note, some statistics data may not be reset including data that are incremental counters."
	::= { ltmRuleEventStat 1 }

ltmRuleEventStatNumber OBJECT-TYPE
	SYNTAX INTEGER
	MAX-ACCESS read-only
	STATUS current
	DESCRIPTION
		"The number of ltmRuleEventStat entries in the table."
	::= { ltmRuleEventStat 2 }

ltmRuleEventStatTable OBJECT-TYPE
	SYNTAX SEQUENCE OF LtmRuleEventStatEntry
	MAX-ACCESS not-accessible
	STATUS current
	DESCRIPTION
		"A table containing statistic information of rules."
	::= { ltmRuleEventStat 3 }

ltmRuleEventStatEntry OBJECT-TYPE
	SYNTAX  LtmRuleEventStatEntry
	MAX-ACCESS not-accessible
	STATUS current
	DESCRIPTION
		"Columns in the ltmRuleEventStat Table"
	INDEX {
		ltmRuleEventStatName,
		ltmRuleEventStatEventType,
		ltmRuleEventStatPriority
	}
	::= { ltmRuleEventStatTable 1 }

LtmRuleEventStatEntry ::=
	SEQUENCE {
        	ltmRuleEventStatName                                      LongDisplayString,
        	ltmRuleEventStatEventType                                 LongDisplayString,
        	ltmRuleEventStatPriority                                  INTEGER,
        	ltmRuleEventStatFailures                                  Gauge,
        	ltmRuleEventStatAborts                                    Gauge,
        	ltmRuleEventStatTotalExecutions                           Gauge,
        	ltmRuleEventStatAvgCycles                                 Gauge,
        	ltmRuleEventStatMaxCycles                                 Gauge,
        	ltmRuleEventStatMinCycles                                 Gauge
	}

ltmRuleEventStatName OBJECT-TYPE
	SYNTAX LongDisplayString
	MAX-ACCESS read-only
	STATUS current
	DESCRIPTION
		"The name of a rule."
	::= { ltmRuleEventStatEntry 1 }

ltmRuleEventStatEventType OBJECT-TYPE
	SYNTAX LongDisplayString
	MAX-ACCESS read-only
	STATUS current
	DESCRIPTION
		"The type of the event associated with the specified rule."
	::= { ltmRuleEventStatEntry 2 }

ltmRuleEventStatPriority OBJECT-TYPE
	SYNTAX INTEGER(0..32767)
	MAX-ACCESS read-only
	STATUS current
	DESCRIPTION
		"The rule execution priority."
	::= { ltmRuleEventStatEntry 3 }

ltmRuleEventStatFailures OBJECT-TYPE
	SYNTAX Gauge
	MAX-ACCESS read-only
	STATUS current
	DESCRIPTION
		"The number of failures for executing the specified rule."
	::= { ltmRuleEventStatEntry 4 }

ltmRuleEventStatAborts OBJECT-TYPE
	SYNTAX Gauge
	MAX-ACCESS read-only
	STATUS current
	DESCRIPTION
		"The number of aborts when executing the specified rule."
	::= { ltmRuleEventStatEntry 5 }

ltmRuleEventStatTotalExecutions OBJECT-TYPE
	SYNTAX Gauge
	MAX-ACCESS read-only
	STATUS current
	DESCRIPTION
		"The total number of event executions for the specified rule."
	::= { ltmRuleEventStatEntry 6 }

ltmRuleEventStatAvgCycles OBJECT-TYPE
	SYNTAX Gauge
	MAX-ACCESS read-only
	STATUS current
	DESCRIPTION
		"The average of cycles spent during an execution of the specified rule event."
	::= { ltmRuleEventStatEntry 7 }

ltmRuleEventStatMaxCycles OBJECT-TYPE
	SYNTAX Gauge
	MAX-ACCESS read-only
	STATUS current
	DESCRIPTION
		"The maximum of cycles spent during an execution of the specified rule event."
	::= { ltmRuleEventStatEntry 8 }

ltmRuleEventStatMinCycles OBJECT-TYPE
	SYNTAX Gauge
	MAX-ACCESS read-only
	STATUS current
	DESCRIPTION
		"The minimum of cycles spent during an execution of the specified rule event."
	::= { ltmRuleEventStatEntry 9 }

--==================================================================
-- Snat
--==================================================================
ltmSnatNumber OBJECT-TYPE
	SYNTAX INTEGER
	MAX-ACCESS read-only
	STATUS current
	DESCRIPTION
		"The number of ltmSnat entries in the table."
	::= { ltmSnat 1 }

ltmSnatTable OBJECT-TYPE
	SYNTAX SEQUENCE OF LtmSnatEntry
	MAX-ACCESS not-accessible
	STATUS current
	DESCRIPTION
		"A table containing information of SNAT."
	::= { ltmSnat 2 }

ltmSnatEntry OBJECT-TYPE
	SYNTAX  LtmSnatEntry
	MAX-ACCESS not-accessible
	STATUS current
	DESCRIPTION
		"Columns in the ltmSnat Table"
	INDEX {
		ltmSnatName
	}
	::= { ltmSnatTable 1 }

LtmSnatEntry ::=
	SEQUENCE {
        	ltmSnatName                                               LongDisplayString,
        	ltmSnatSfFlags                                            INTEGER,
        	ltmSnatType                                               INTEGER,
        	ltmSnatTransAddrType                                      InetAddressType,
        	ltmSnatTransAddr                                          InetAddress,
        	ltmSnatSnatpoolName                                       LongDisplayString,
        	ltmSnatListedEnabledVlans                                 INTEGER,
        	ltmSnatTransAddrName                                      LongDisplayString
	}

ltmSnatName OBJECT-TYPE
	SYNTAX LongDisplayString
	MAX-ACCESS read-only
	STATUS current
	DESCRIPTION
		"The name of a SNAT. It is a named object in the definition of
		a standard or a selective SNAT. Standard SNATs translate to
		a single address, while selective SNATs translate to a pool of
		translation addresses."
	::= { ltmSnatEntry 1 }

ltmSnatSfFlags OBJECT-TYPE
	SYNTAX INTEGER {
		disabled(0),
		enabled(1)
	}
	MAX-ACCESS read-only
	STATUS current
	DESCRIPTION
		"The state indicating whether connection mirroring is
		enabled or not for the specified SNAT."
	::= { ltmSnatEntry 2 }

ltmSnatType OBJECT-TYPE
	SYNTAX INTEGER {
		none(0),
		transaddr(1),
		snatpool(2),
		automap(3)
	}
	MAX-ACCESS read-only
	STATUS current
	DESCRIPTION
		"The translation type of the specified SNAT.
		none - No SNAT (invalid default);
		transaddr - The SNAT uses a single translation address;
		snatpool - The SNAT uses a SNAT pool of translation addresses;
		automap - The SNAT uses self IP addresses."
	::= { ltmSnatEntry 3 }

ltmSnatTransAddrType OBJECT-TYPE
	SYNTAX InetAddressType
	MAX-ACCESS read-only
	STATUS current
	DESCRIPTION
		"The IP address type of ltmSnatTransAddr"
	::= { ltmSnatEntry 4 }

ltmSnatTransAddr OBJECT-TYPE
	SYNTAX InetAddress
	MAX-ACCESS read-only
	STATUS current
	DESCRIPTION
		"The translation address used by the specified SNAT
		if the SNAT translates to a translation address.
		It is interpreted within the context of a ltmSnatTransAddrType value."
	::= { ltmSnatEntry 5 }

ltmSnatSnatpoolName OBJECT-TYPE
	SYNTAX LongDisplayString
	MAX-ACCESS read-only
	STATUS current
	DESCRIPTION
		"The name of a SNAT pool, which is a pool of SNAT translation addresses.
		It is used by the specified SNAT if the SNAT translates to a pool."
	::= { ltmSnatEntry 6 }

ltmSnatListedEnabledVlans OBJECT-TYPE
	SYNTAX INTEGER {
		false(0),
		true(1)
	}
	MAX-ACCESS read-only
	STATUS current
	DESCRIPTION
		"The state indicating whether associated VLANs are SNAT enabled or not.
		The associated VLANs are listed in ltmSnatVlanTable."
	::= { ltmSnatEntry 7 }

ltmSnatTransAddrName OBJECT-TYPE
	SYNTAX LongDisplayString
	MAX-ACCESS read-only
	STATUS current
	DESCRIPTION
		"Translation Name"
	::= { ltmSnatEntry 8 }

--==================================================================
-- Snat_stat
--==================================================================
ltmSnatStatResetStats OBJECT-TYPE
	SYNTAX INTEGER
	MAX-ACCESS read-write
	STATUS current
	DESCRIPTION
		"The action to reset resettable statistics data in ltmSnatStat.
		 Setting this value to 1 will reset statistics data.
		 Note, some statistics data may not be reset including data that are incremental counters."
	::= { ltmSnatStat 1 }

ltmSnatStatNumber OBJECT-TYPE
	SYNTAX INTEGER
	MAX-ACCESS read-only
	STATUS current
	DESCRIPTION
		"The number of ltmSnatStat entries in the table."
	::= { ltmSnatStat 2 }

ltmSnatStatTable OBJECT-TYPE
	SYNTAX SEQUENCE OF LtmSnatStatEntry
	MAX-ACCESS not-accessible
	STATUS current
	DESCRIPTION
		"A table containing statistic information of SNAT."
	::= { ltmSnatStat 3 }

ltmSnatStatEntry OBJECT-TYPE
	SYNTAX  LtmSnatStatEntry
	MAX-ACCESS not-accessible
	STATUS current
	DESCRIPTION
		"Columns in the ltmSnatStat Table"
	INDEX {
		ltmSnatStatName
	}
	::= { ltmSnatStatTable 1 }

LtmSnatStatEntry ::=
	SEQUENCE {
        	ltmSnatStatName                                           LongDisplayString,
        	ltmSnatStatClientPktsIn                                   Counter64,
        	ltmSnatStatClientBytesIn                                  Counter64,
        	ltmSnatStatClientPktsOut                                  Counter64,
        	ltmSnatStatClientBytesOut                                 Counter64,
        	ltmSnatStatClientMaxConns                                 Counter64,
        	ltmSnatStatClientTotConns                                 Counter64,
        	ltmSnatStatClientCurConns                                 Gauge
	}

ltmSnatStatName OBJECT-TYPE
	SYNTAX LongDisplayString
	MAX-ACCESS read-only
	STATUS current
	DESCRIPTION
		"The name of a SNAT."
	::= { ltmSnatStatEntry 1 }

ltmSnatStatClientPktsIn OBJECT-TYPE
	SYNTAX Counter64
	MAX-ACCESS read-only
	STATUS current
	DESCRIPTION
		"The number of packets received from client-side."
	::= { ltmSnatStatEntry 2 }

ltmSnatStatClientBytesIn OBJECT-TYPE
	SYNTAX Counter64
	MAX-ACCESS read-only
	STATUS current
	DESCRIPTION
		"The number of bytes received from client-side."
	::= { ltmSnatStatEntry 3 }

ltmSnatStatClientPktsOut OBJECT-TYPE
	SYNTAX Counter64
	MAX-ACCESS read-only
	STATUS current
	DESCRIPTION
		"The number of packets sent to client-side."
	::= { ltmSnatStatEntry 4 }

ltmSnatStatClientBytesOut OBJECT-TYPE
	SYNTAX Counter64
	MAX-ACCESS read-only
	STATUS current
	DESCRIPTION
		"The number of bytes sent to client-side."
	::= { ltmSnatStatEntry 5 }

ltmSnatStatClientMaxConns OBJECT-TYPE
	SYNTAX Counter64
	MAX-ACCESS read-only
	STATUS current
	DESCRIPTION
		"The maximum connections from client-side."
	::= { ltmSnatStatEntry 6 }

ltmSnatStatClientTotConns OBJECT-TYPE
	SYNTAX Counter64
	MAX-ACCESS read-only
	STATUS current
	DESCRIPTION
		"The total connections from client-side."
	::= { ltmSnatStatEntry 7 }

ltmSnatStatClientCurConns OBJECT-TYPE
	SYNTAX Gauge
	MAX-ACCESS read-only
	STATUS current
	DESCRIPTION
		"The current connections from client-side."
	::= { ltmSnatStatEntry 8 }

--==================================================================
-- Snat_vlan
--==================================================================
ltmSnatVlanNumber OBJECT-TYPE
	SYNTAX INTEGER
	MAX-ACCESS read-only
	STATUS current
	DESCRIPTION
		"The number of ltmSnatVlan entries in the table."
	::= { ltmSnatVlan 1 }

ltmSnatVlanTable OBJECT-TYPE
	SYNTAX SEQUENCE OF LtmSnatVlanEntry
	MAX-ACCESS not-accessible
	STATUS current
	DESCRIPTION
		"A table containing VLAN information associated with SNAT."
	::= { ltmSnatVlan 2 }

ltmSnatVlanEntry OBJECT-TYPE
	SYNTAX  LtmSnatVlanEntry
	MAX-ACCESS not-accessible
	STATUS current
	DESCRIPTION
		"Columns in the ltmSnatVlan Table"
	INDEX {
		ltmSnatVlanSnatName,
		ltmSnatVlanVlanName
	}
	::= { ltmSnatVlanTable 1 }

LtmSnatVlanEntry ::=
	SEQUENCE {
        	ltmSnatVlanSnatName                                       LongDisplayString,
        	ltmSnatVlanVlanName                                       LongDisplayString
	}

ltmSnatVlanSnatName OBJECT-TYPE
	SYNTAX LongDisplayString
	MAX-ACCESS read-only
	STATUS current
	DESCRIPTION
		"The name of a SNAT."
	::= { ltmSnatVlanEntry 1 }

ltmSnatVlanVlanName OBJECT-TYPE
	SYNTAX LongDisplayString
	MAX-ACCESS read-only
	STATUS current
	DESCRIPTION
		"The name of a VLAN associated with the specified SNAT.
		Only when ltmSnatListedEnabledVlans is set to enable,
		SNAT is enabled on the VLAN. "
	::= { ltmSnatVlanEntry 2 }

--==================================================================
-- Snat_orig_addr
--==================================================================
ltmSnatOrigAddrNumber OBJECT-TYPE
	SYNTAX INTEGER
	MAX-ACCESS read-only
	STATUS current
	DESCRIPTION
		"The number of ltmSnatOrigAddr entries in the table."
	::= { ltmSnatOrigAddr 1 }

ltmSnatOrigAddrTable OBJECT-TYPE
	SYNTAX SEQUENCE OF LtmSnatOrigAddrEntry
	MAX-ACCESS not-accessible
	STATUS current
	DESCRIPTION
		"A table containing information of SNAT original addresses."
	::= { ltmSnatOrigAddr 2 }

ltmSnatOrigAddrEntry OBJECT-TYPE
	SYNTAX  LtmSnatOrigAddrEntry
	MAX-ACCESS not-accessible
	STATUS current
	DESCRIPTION
		"Columns in the ltmSnatOrigAddr Table"
	INDEX {
		ltmSnatOrigAddrSnatName,
		ltmSnatOrigAddrAddrType,
		ltmSnatOrigAddrAddr,
		ltmSnatOrigAddrWildmaskType,
		ltmSnatOrigAddrWildmask
	}
	::= { ltmSnatOrigAddrTable 1 }

LtmSnatOrigAddrEntry ::=
	SEQUENCE {
        	ltmSnatOrigAddrSnatName                                   LongDisplayString,
        	ltmSnatOrigAddrAddrType                                   InetAddressType,
        	ltmSnatOrigAddrAddr                                       InetAddress,
        	ltmSnatOrigAddrWildmaskType                               InetAddressType,
        	ltmSnatOrigAddrWildmask                                   InetAddress
	}

ltmSnatOrigAddrSnatName OBJECT-TYPE
	SYNTAX LongDisplayString
	MAX-ACCESS read-only
	STATUS current
	DESCRIPTION
		"The name of a SNAT."
	::= { ltmSnatOrigAddrEntry 1 }

ltmSnatOrigAddrAddrType OBJECT-TYPE
	SYNTAX InetAddressType
	MAX-ACCESS read-only
	STATUS current
	DESCRIPTION
		"The IP address type of ltmSnatOrigAddrAddr"
	::= { ltmSnatOrigAddrEntry 2 }

ltmSnatOrigAddrAddr OBJECT-TYPE
	SYNTAX InetAddress
	MAX-ACCESS read-only
	STATUS current
	DESCRIPTION
		"The original client address associated with the specified SNAT.
		It is interpreted within the context of a ltmSnatOrigAddrAddrType value."
	::= { ltmSnatOrigAddrEntry 3 }

ltmSnatOrigAddrWildmaskType OBJECT-TYPE
	SYNTAX InetAddressType
	MAX-ACCESS read-only
	STATUS current
	DESCRIPTION
		"The IP address type of ltmSnatOrigWidemask"
	::= { ltmSnatOrigAddrEntry 4 }

ltmSnatOrigAddrWildmask OBJECT-TYPE
	SYNTAX InetAddress
	MAX-ACCESS read-only
	STATUS current
	DESCRIPTION
		"The wildcard netmask associated with the specified SNAT original address.
		It is interpreted within the context of a ltmSnatOrigAddrWidemaskType value."
	::= { ltmSnatOrigAddrEntry 5 }

--==================================================================
-- Trans_addr
--==================================================================
ltmTransAddrNumber OBJECT-TYPE
	SYNTAX INTEGER
	MAX-ACCESS read-only
	STATUS current
	DESCRIPTION
		"The number of ltmTransAddr entries in the table."
	::= { ltmTransAddr 1 }

ltmTransAddrTable OBJECT-TYPE
	SYNTAX SEQUENCE OF LtmTransAddrEntry
	MAX-ACCESS not-accessible
	STATUS current
	DESCRIPTION
		"A table containing information of SNAT translated addresses."
	::= { ltmTransAddr 2 }

ltmTransAddrEntry OBJECT-TYPE
	SYNTAX  LtmTransAddrEntry
	MAX-ACCESS not-accessible
	STATUS current
	DESCRIPTION
		"Columns in the ltmTransAddr Table"
	INDEX {
		ltmTransAddrName
	}
	::= { ltmTransAddrTable 1 }

LtmTransAddrEntry ::=
	SEQUENCE {
        	ltmTransAddrAddrType                                      InetAddressType,
        	ltmTransAddrAddr                                          InetAddress,
        	ltmTransAddrEnabled                                       INTEGER,
        	ltmTransAddrConnLimit                                     Gauge,
        	ltmTransAddrTcpIdleTimeout                                Gauge,
        	ltmTransAddrUdpIdleTimeout                                Gauge,
        	ltmTransAddrIpIdleTimeout                                 Gauge,
        	ltmTransAddrArpEnabled                                    INTEGER,
        	ltmTransAddrUnitId                                        Gauge,
        	ltmTransAddrName                                          LongDisplayString
	}

ltmTransAddrAddrType OBJECT-TYPE
	SYNTAX InetAddressType
	MAX-ACCESS read-only
	STATUS current
	DESCRIPTION
		"The IP address type of ltmTransAddrAddr"
	::= { ltmTransAddrEntry 1 }

ltmTransAddrAddr OBJECT-TYPE
	SYNTAX InetAddress
	MAX-ACCESS read-only
	STATUS current
	DESCRIPTION
		"The SNAT translation address for use as a server-side client address.
		on the server-side. It is interpreted within the context of
		an ltmTransAddrAddrType value."
	::= { ltmTransAddrEntry 2 }

ltmTransAddrEnabled OBJECT-TYPE
	SYNTAX INTEGER {
		false(0),
		true(1)
	}
	MAX-ACCESS read-only
	STATUS current
	DESCRIPTION
		"The state indicating whether the specified SNAT translation address is enabled or not."
	::= { ltmTransAddrEntry 3 }

ltmTransAddrConnLimit OBJECT-TYPE
	SYNTAX Gauge
	MAX-ACCESS read-only
	STATUS current
	DESCRIPTION
		"The maximum number of connections the specified SNAT translation address is
		 allowed to have open at one time."
	::= { ltmTransAddrEntry 4 }

ltmTransAddrTcpIdleTimeout OBJECT-TYPE
	SYNTAX Gauge
	MAX-ACCESS read-only
	STATUS current
	DESCRIPTION
		"The TCP idle timeout (in seconds) of the SNAT specified translation address."
	::= { ltmTransAddrEntry 5 }

ltmTransAddrUdpIdleTimeout OBJECT-TYPE
	SYNTAX Gauge
	MAX-ACCESS read-only
	STATUS current
	DESCRIPTION
		"The UDP idle timeout (in seconds) of the specified SNAT translation address."
	::= { ltmTransAddrEntry 6 }

ltmTransAddrIpIdleTimeout OBJECT-TYPE
	SYNTAX Gauge
	MAX-ACCESS read-only
	STATUS current
	DESCRIPTION
		"The IP idle timeout (in seconds) of the specified SNAT translation address."
	::= { ltmTransAddrEntry 7 }

ltmTransAddrArpEnabled OBJECT-TYPE
	SYNTAX INTEGER {
		false(0),
		true(1)
	}
	MAX-ACCESS read-only
	STATUS current
	DESCRIPTION
		"The state indicating whether ARP is enabled or not for the specified SNAT translation address."
	::= { ltmTransAddrEntry 8 }

ltmTransAddrUnitId OBJECT-TYPE
	SYNTAX Gauge
	MAX-ACCESS read-only
	STATUS current
	DESCRIPTION
		"The unit number associated with the specified SNAT translation address."
	::= { ltmTransAddrEntry 9 }

ltmTransAddrName OBJECT-TYPE
	SYNTAX LongDisplayString
	MAX-ACCESS read-only
	STATUS current
	DESCRIPTION
		"name of trans addr"
	::= { ltmTransAddrEntry 10 }

--==================================================================
-- Trans_addr_stat
--==================================================================
ltmTransAddrStatResetStats OBJECT-TYPE
	SYNTAX INTEGER
	MAX-ACCESS read-write
	STATUS current
	DESCRIPTION
		"The action to reset resettable statistics data in ltmTransAddrStat.
		 Setting this value to 1 will reset statistics data.
		 Note, some statistics data may not be reset including data that are incremental counters."
	::= { ltmTransAddrStat 1 }

ltmTransAddrStatNumber OBJECT-TYPE
	SYNTAX INTEGER
	MAX-ACCESS read-only
	STATUS current
	DESCRIPTION
		"The number of ltmTransAddrStat entries in the table."
	::= { ltmTransAddrStat 2 }

ltmTransAddrStatTable OBJECT-TYPE
	SYNTAX SEQUENCE OF LtmTransAddrStatEntry
	MAX-ACCESS not-accessible
	STATUS current
	DESCRIPTION
		"A table containing statistic information of SNAT translated addresses."
	::= { ltmTransAddrStat 3 }

ltmTransAddrStatEntry OBJECT-TYPE
	SYNTAX  LtmTransAddrStatEntry
	MAX-ACCESS not-accessible
	STATUS current
	DESCRIPTION
		"Columns in the ltmTransAddrStat Table"
	INDEX {
		ltmTransAddrStatName
	}
	::= { ltmTransAddrStatTable 1 }

LtmTransAddrStatEntry ::=
	SEQUENCE {
        	ltmTransAddrStatAddrType                                  InetAddressType,
        	ltmTransAddrStatAddr                                      InetAddress,
        	ltmTransAddrStatServerPktsIn                              Counter64,
        	ltmTransAddrStatServerBytesIn                             Counter64,
        	ltmTransAddrStatServerPktsOut                             Counter64,
        	ltmTransAddrStatServerBytesOut                            Counter64,
        	ltmTransAddrStatServerMaxConns                            Counter64,
        	ltmTransAddrStatServerTotConns                            Counter64,
        	ltmTransAddrStatServerCurConns                            Gauge,
        	ltmTransAddrStatName                                      LongDisplayString
	}

ltmTransAddrStatAddrType OBJECT-TYPE
	SYNTAX InetAddressType
	MAX-ACCESS read-only
	STATUS	 deprecated
	DESCRIPTION
		"Deprecated!  Use name as index
	    The IP address type of ltmTransAddrStatAddr"
	::= { ltmTransAddrStatEntry 1 }

ltmTransAddrStatAddr OBJECT-TYPE
	SYNTAX InetAddress
	MAX-ACCESS read-only
	STATUS	 deprecated
	DESCRIPTION
		"Deprecated!  Use name as index
		The SNAT translation address for use as a server-side client address.
		on the server-side. It is interpreted within the context of
		an ltmTransAddrStatAddrType value."
	::= { ltmTransAddrStatEntry 2 }

ltmTransAddrStatServerPktsIn OBJECT-TYPE
	SYNTAX Counter64
	MAX-ACCESS read-only
	STATUS current
	DESCRIPTION
		"The number of packets received from server-side."
	::= { ltmTransAddrStatEntry 3 }

ltmTransAddrStatServerBytesIn OBJECT-TYPE
	SYNTAX Counter64
	MAX-ACCESS read-only
	STATUS current
	DESCRIPTION
		"The number of bytes received from server-side."
	::= { ltmTransAddrStatEntry 4 }

ltmTransAddrStatServerPktsOut OBJECT-TYPE
	SYNTAX Counter64
	MAX-ACCESS read-only
	STATUS current
	DESCRIPTION
		"The number of packets sent to server-side."
	::= { ltmTransAddrStatEntry 5 }

ltmTransAddrStatServerBytesOut OBJECT-TYPE
	SYNTAX Counter64
	MAX-ACCESS read-only
	STATUS current
	DESCRIPTION
		"The number of bytes sent to server-side."
	::= { ltmTransAddrStatEntry 6 }

ltmTransAddrStatServerMaxConns OBJECT-TYPE
	SYNTAX Counter64
	MAX-ACCESS read-only
	STATUS current
	DESCRIPTION
		"The maximum connections from server-side."
	::= { ltmTransAddrStatEntry 7 }

ltmTransAddrStatServerTotConns OBJECT-TYPE
	SYNTAX Counter64
	MAX-ACCESS read-only
	STATUS current
	DESCRIPTION
		"The total connections from server-side."
	::= { ltmTransAddrStatEntry 8 }

ltmTransAddrStatServerCurConns OBJECT-TYPE
	SYNTAX Gauge
	MAX-ACCESS read-only
	STATUS current
	DESCRIPTION
		"The current connections from server-side."
	::= { ltmTransAddrStatEntry 9 }

ltmTransAddrStatName OBJECT-TYPE
	SYNTAX LongDisplayString
	MAX-ACCESS read-only
	STATUS current
	DESCRIPTION
		"name of trans addr stat"
	::= { ltmTransAddrStatEntry 10 }

--==================================================================
-- Snatpool
--==================================================================
ltmSnatPoolNumber OBJECT-TYPE
	SYNTAX INTEGER
	MAX-ACCESS read-only
	STATUS current
	DESCRIPTION
		"The number of ltmSnatPool entries in the table."
	::= { ltmSnatPool 1 }

ltmSnatPoolTable OBJECT-TYPE
	SYNTAX SEQUENCE OF LtmSnatPoolEntry
	MAX-ACCESS not-accessible
	STATUS current
	DESCRIPTION
		"A table containing information of SNAT pools."
	::= { ltmSnatPool 2 }

ltmSnatPoolEntry OBJECT-TYPE
	SYNTAX  LtmSnatPoolEntry
	MAX-ACCESS not-accessible
	STATUS current
	DESCRIPTION
		"Columns in the ltmSnatPool Table"
	INDEX {
		ltmSnatPoolName
	}
	::= { ltmSnatPoolTable 1 }

LtmSnatPoolEntry ::=
	SEQUENCE {
        	ltmSnatPoolName                                           LongDisplayString
	}

ltmSnatPoolName OBJECT-TYPE
	SYNTAX LongDisplayString
	MAX-ACCESS read-only
	STATUS current
	DESCRIPTION
		"The name of a SNAT pool, which is a pool of SNAT translation addresses."
	::= { ltmSnatPoolEntry 1 }

--==================================================================
-- Snatpool_stat
--==================================================================
ltmSnatPoolStatResetStats OBJECT-TYPE
	SYNTAX INTEGER
	MAX-ACCESS read-write
	STATUS current
	DESCRIPTION
		"The action to reset resettable statistics data in ltmSnatPoolStat.
		 Setting this value to 1 will reset statistics data.
		 Note, some statistics data may not be reset including data that are incremental counters."
	::= { ltmSnatPoolStat 1 }

ltmSnatPoolStatNumber OBJECT-TYPE
	SYNTAX INTEGER
	MAX-ACCESS read-only
	STATUS current
	DESCRIPTION
		"The number of ltmSnatPoolStat entries in the table."
	::= { ltmSnatPoolStat 2 }

ltmSnatPoolStatTable OBJECT-TYPE
	SYNTAX SEQUENCE OF LtmSnatPoolStatEntry
	MAX-ACCESS not-accessible
	STATUS current
	DESCRIPTION
		"A table containing statistic information of SNAT pools."
	::= { ltmSnatPoolStat 3 }

ltmSnatPoolStatEntry OBJECT-TYPE
	SYNTAX  LtmSnatPoolStatEntry
	MAX-ACCESS not-accessible
	STATUS current
	DESCRIPTION
		"Columns in the ltmSnatPoolStat Table"
	INDEX {
		ltmSnatPoolStatName
	}
	::= { ltmSnatPoolStatTable 1 }

LtmSnatPoolStatEntry ::=
	SEQUENCE {
        	ltmSnatPoolStatName                                       LongDisplayString,
        	ltmSnatPoolStatServerPktsIn                               Counter64,
        	ltmSnatPoolStatServerBytesIn                              Counter64,
        	ltmSnatPoolStatServerPktsOut                              Counter64,
        	ltmSnatPoolStatServerBytesOut                             Counter64,
        	ltmSnatPoolStatServerMaxConns                             Counter64,
        	ltmSnatPoolStatServerTotConns                             Counter64,
        	ltmSnatPoolStatServerCurConns                             Gauge
	}

ltmSnatPoolStatName OBJECT-TYPE
	SYNTAX LongDisplayString
	MAX-ACCESS read-only
	STATUS current
	DESCRIPTION
		"The name of the SNAT pool."
	::= { ltmSnatPoolStatEntry 1 }

ltmSnatPoolStatServerPktsIn OBJECT-TYPE
	SYNTAX Counter64
	MAX-ACCESS read-only
	STATUS current
	DESCRIPTION
		"The number of packets received from server-side."
	::= { ltmSnatPoolStatEntry 2 }

ltmSnatPoolStatServerBytesIn OBJECT-TYPE
	SYNTAX Counter64
	MAX-ACCESS read-only
	STATUS current
	DESCRIPTION
		"The number of bytes received from server-side."
	::= { ltmSnatPoolStatEntry 3 }

ltmSnatPoolStatServerPktsOut OBJECT-TYPE
	SYNTAX Counter64
	MAX-ACCESS read-only
	STATUS current
	DESCRIPTION
		"The number of packets sent to server-side."
	::= { ltmSnatPoolStatEntry 4 }

ltmSnatPoolStatServerBytesOut OBJECT-TYPE
	SYNTAX Counter64
	MAX-ACCESS read-only
	STATUS current
	DESCRIPTION
		"The number of bytes sent to server-side."
	::= { ltmSnatPoolStatEntry 5 }

ltmSnatPoolStatServerMaxConns OBJECT-TYPE
	SYNTAX Counter64
	MAX-ACCESS read-only
	STATUS current
	DESCRIPTION
		"The maximum connections from server-side."
	::= { ltmSnatPoolStatEntry 6 }

ltmSnatPoolStatServerTotConns OBJECT-TYPE
	SYNTAX Counter64
	MAX-ACCESS read-only
	STATUS current
	DESCRIPTION
		"The total connections from server-side."
	::= { ltmSnatPoolStatEntry 7 }

ltmSnatPoolStatServerCurConns OBJECT-TYPE
	SYNTAX Gauge
	MAX-ACCESS read-only
	STATUS current
	DESCRIPTION
		"The current connections from server-side."
	::= { ltmSnatPoolStatEntry 8 }

--==================================================================
-- Snatpool_trans_addr
--==================================================================
ltmSnatpoolTransAddrNumber OBJECT-TYPE
	SYNTAX INTEGER
	MAX-ACCESS read-only
	STATUS current
	DESCRIPTION
		"The number of ltmSnatpoolTransAddr entries in the table."
	::= { ltmSnatpoolTransAddr 1 }

ltmSnatpoolTransAddrTable OBJECT-TYPE
	SYNTAX SEQUENCE OF LtmSnatpoolTransAddrEntry
	MAX-ACCESS not-accessible
	STATUS current
	DESCRIPTION
		"A table containing information of joining SnatPool to TransAddr."
	::= { ltmSnatpoolTransAddr 2 }

ltmSnatpoolTransAddrEntry OBJECT-TYPE
	SYNTAX  LtmSnatpoolTransAddrEntry
	MAX-ACCESS not-accessible
	STATUS current
	DESCRIPTION
		"Columns in the ltmSnatpoolTransAddr Table"
	INDEX {
		ltmSnatpoolTransAddrSnatpoolName,
		ltmSnatpoolTransAddrTransAddrName
	}
	::= { ltmSnatpoolTransAddrTable 1 }

LtmSnatpoolTransAddrEntry ::=
	SEQUENCE {
        	ltmSnatpoolTransAddrSnatpoolName                          LongDisplayString,
        	ltmSnatpoolTransAddrTransAddrType                         InetAddressType,
        	ltmSnatpoolTransAddrTransAddr                             InetAddress,
        	ltmSnatpoolTransAddrTransAddrName                         LongDisplayString
	}

ltmSnatpoolTransAddrSnatpoolName OBJECT-TYPE
	SYNTAX LongDisplayString
	MAX-ACCESS read-only
	STATUS current
	DESCRIPTION
		"The name of a SNAT pool."
	::= { ltmSnatpoolTransAddrEntry 1 }

ltmSnatpoolTransAddrTransAddrType OBJECT-TYPE
	SYNTAX InetAddressType
	MAX-ACCESS read-only
	STATUS current
	DESCRIPTION
		"The IP address type of ltmTransAddrAddr"
	::= { ltmSnatpoolTransAddrEntry 2 }

ltmSnatpoolTransAddrTransAddr OBJECT-TYPE
	SYNTAX InetAddress
	MAX-ACCESS read-only
	STATUS current
	DESCRIPTION
		"The SNAT translation address associated with the specified SNAT pool.,
		It is interpreted within the context of an ltmSnatpoolTransAddrTransAddrType value."
	::= { ltmSnatpoolTransAddrEntry 3 }

ltmSnatpoolTransAddrTransAddrName OBJECT-TYPE
	SYNTAX LongDisplayString
	MAX-ACCESS read-only
	STATUS current
	DESCRIPTION
		"The name of a trans_addr."
	::= { ltmSnatpoolTransAddrEntry 4 }

--==================================================================
-- Virtual_server
--==================================================================
ltmVirtualServNumber OBJECT-TYPE
	SYNTAX INTEGER
	MAX-ACCESS read-only
	STATUS current
	DESCRIPTION
		"The number of ltmVirtualServ entries in the table."
	::= { ltmVirtualServ 1 }

ltmVirtualServTable OBJECT-TYPE
	SYNTAX SEQUENCE OF LtmVirtualServEntry
	MAX-ACCESS not-accessible
	STATUS current
	DESCRIPTION
		"A table containing information of virtual servers."
	::= { ltmVirtualServ 2 }

ltmVirtualServEntry OBJECT-TYPE
	SYNTAX  LtmVirtualServEntry
	MAX-ACCESS not-accessible
	STATUS current
	DESCRIPTION
		"Columns in the ltmVirtualServ Table"
	INDEX {
		ltmVirtualServName
	}
	::= { ltmVirtualServTable 1 }

LtmVirtualServEntry ::=
	SEQUENCE {
        	ltmVirtualServName                                        LongDisplayString,
        	ltmVirtualServAddrType                                    InetAddressType,
        	ltmVirtualServAddr                                        InetAddress,
        	ltmVirtualServWildmaskType                                InetAddressType,
        	ltmVirtualServWildmask                                    InetAddress,
        	ltmVirtualServPort                                        InetPortNumber,
        	ltmVirtualServIpProto                                     INTEGER,
        	ltmVirtualServListedEnabledVlans                          INTEGER,
        	ltmVirtualServEnabled                                     INTEGER,
        	ltmVirtualServConnLimit                                   Gauge,
        	ltmVirtualServRclass                                      LongDisplayString,
        	ltmVirtualServSfFlags                                     INTEGER,
        	ltmVirtualServTranslateAddr                               INTEGER,
        	ltmVirtualServTranslatePort                               INTEGER,
        	ltmVirtualServType                                        INTEGER,
        	ltmVirtualServSnatType                                    INTEGER,
        	ltmVirtualServLasthopPoolName                             LongDisplayString,
        	ltmVirtualServSnatpoolName                                LongDisplayString,
        	ltmVirtualServDefaultPool                                 LongDisplayString,
        	ltmVirtualServFallbackPersist                             LongDisplayString,
        	ltmVirtualServActualPvaAccel                              INTEGER,
        	ltmVirtualServAvailabilityState                           INTEGER,
        	ltmVirtualServEnabledState                                INTEGER,
        	ltmVirtualServDisabledParentType                          Gauge,
        	ltmVirtualServStatusReason                                LongDisplayString,
        	ltmVirtualServGtmScore                                    Gauge,
        	ltmVirtualServCmpEnabled                                  INTEGER,
        	ltmVirtualServSrcport                                     INTEGER,
        	ltmVirtualServVaName                                      LongDisplayString,
        	ltmVirtualServSourceAddressTranslationType                INTEGER,
        	ltmVirtualServSourceAddressTranslationPool                LongDisplayString,
        	ltmVirtualServServiceDownImmediateAction                  INTEGER,
        	ltmVirtualServServersslUseSni                             INTEGER
	}

ltmVirtualServName OBJECT-TYPE
	SYNTAX LongDisplayString
	MAX-ACCESS read-only
	STATUS current
	DESCRIPTION
		"The name of a virtual server."
	::= { ltmVirtualServEntry 1 }

ltmVirtualServAddrType OBJECT-TYPE
	SYNTAX InetAddressType
	MAX-ACCESS read-only
	STATUS current
	DESCRIPTION
		"The IP address type of ltmVirtualServAddr."
	::= { ltmVirtualServEntry 2 }

ltmVirtualServAddr OBJECT-TYPE
	SYNTAX InetAddress
	MAX-ACCESS read-only
	STATUS current
	DESCRIPTION
		"The IP address of the specified virtual server. It is interpreted
		 within the context of an ltmVitualServAddrType value."
	::= { ltmVirtualServEntry 3 }

ltmVirtualServWildmaskType OBJECT-TYPE
	SYNTAX InetAddressType
	MAX-ACCESS read-only
	STATUS current
	DESCRIPTION
		"The IP address type of ltmVirtualServWildmask."
	::= { ltmVirtualServEntry 4 }

ltmVirtualServWildmask OBJECT-TYPE
	SYNTAX InetAddress
	MAX-ACCESS read-only
	STATUS current
	DESCRIPTION
		"The wildcard netmask of the specified virtual server. It is interpreted
		 within the context of an ltmVitualServWildmaskType value."
	::= { ltmVirtualServEntry 5 }

ltmVirtualServPort OBJECT-TYPE
	SYNTAX InetPortNumber
	MAX-ACCESS read-only
	STATUS current
	DESCRIPTION
		"The port number of the specified virtual server."
	::= { ltmVirtualServEntry 6 }

ltmVirtualServIpProto OBJECT-TYPE
	SYNTAX INTEGER
	MAX-ACCESS read-only
	STATUS current
	DESCRIPTION
		"The IP protocol (see RFC 1340) used by the specified virtual server."
	::= { ltmVirtualServEntry 7 }

ltmVirtualServListedEnabledVlans OBJECT-TYPE
	SYNTAX INTEGER {
		false(0),
		true(1)
	}
	MAX-ACCESS read-only
	STATUS current
	DESCRIPTION
		"The state indicating whether the specified virtual server is listed
		as enabled or not on associated VLANs. The associated VLANs are
		defined in ltmVirtualServVlanTable."
	::= { ltmVirtualServEntry 8 }

ltmVirtualServEnabled OBJECT-TYPE
	SYNTAX INTEGER {
		false(0),
		true(1)
	}
	MAX-ACCESS read-write
	STATUS current
	DESCRIPTION
		"The state indicating whether the specified virtual server is enabled or not."
	::= { ltmVirtualServEntry 9 }

ltmVirtualServConnLimit OBJECT-TYPE
	SYNTAX Gauge
	MAX-ACCESS read-only
	STATUS current
	DESCRIPTION
		"The maximum number of connections the specified virtual server is allowed
		 to have open at one time."
	::= { ltmVirtualServEntry 10 }

ltmVirtualServRclass OBJECT-TYPE
	SYNTAX LongDisplayString
	MAX-ACCESS read-only
	STATUS current
	DESCRIPTION
		"The rate class that will be used to rate limit the traffic in
		the specified virtual server."
	::= { ltmVirtualServEntry 11 }

ltmVirtualServSfFlags OBJECT-TYPE
	SYNTAX INTEGER {
		disabled(0),
		enabled(1)
	}
	MAX-ACCESS read-only
	STATUS current
	DESCRIPTION
		"The flag to indicate whether connection mirroring is
		enabled or not for the specified virtual server."
	::= { ltmVirtualServEntry 12 }

ltmVirtualServTranslateAddr OBJECT-TYPE
	SYNTAX INTEGER {
		false(0),
		true(1)
	}
	MAX-ACCESS read-only
	STATUS current
	DESCRIPTION
		"The state indicating whether the address of the specified virtual server
		should be translated."
	::= { ltmVirtualServEntry 13 }

ltmVirtualServTranslatePort OBJECT-TYPE
	SYNTAX INTEGER {
		false(0),
		true(1)
	}
	MAX-ACCESS read-only
	STATUS current
	DESCRIPTION
		"The state indicating whether the port of the specified virtual server
		should be translated."
	::= { ltmVirtualServEntry 14 }

ltmVirtualServType OBJECT-TYPE
	SYNTAX INTEGER {
		poolbased(0),
		ipforward(1),
		l2forward(2),
		reject(3),
		fastl4(4),
		fasthttp(5),
		stateless(6),
		dhcpRelay(7),
		internal(8)
	}
	MAX-ACCESS read-only
	STATUS current
	DESCRIPTION
		"The type supported by the specified virtual server.
		poolbased - The virtual server is based on a pool;
		ipforward - The virtual server only supports IP forwarding.
		            There is no load balancing on this type of virtual server;
		l2forward - The virtual server only supports L2 forwarding.
		            There is no load balancing on this type of virtual server;
		reject - All connections going to this virtual server will be rejected, and resets will be sent;
		fastl4 - The virtual server is associated with a Fast L4 profile;
		fasthttp - The virtual server is associated with a Fast HTTP profile;
		stateless - The virtual server accepts traffic matching the virtual server
		            address and load balances the packet to the pool members without
		            attempting to match the packet to a pre-existing connection on the connection
		            table;
		dhcpRelay - The virtual server relays DHCP client requests for an IP address to
		            one or more DHCP servers and provides DHCP server responses with
		            an available IP address for the client;
		internal - The virtual server supports modification of HTTP requests and responses."
	::= { ltmVirtualServEntry 15 }

ltmVirtualServSnatType OBJECT-TYPE
	SYNTAX INTEGER {
		none(0),
		transaddr(1),
		snatpool(2),
		automap(3)
	}
	MAX-ACCESS read-only
	STATUS	 deprecated
	DESCRIPTION
		"Deprecated! Replaced by Source Address Translation type associated with the specified virtual server.
	       The type of SNAT associated with the specified virtual server.
		none - No SNAT used by the virtual server;
		transaddr - The SNAT uses a single translation address (invalid type);
		snatpool - The SNAT uses a SNAT pool of translation addresses;
		automap - The SNAT uses self IP addresses."
	::= { ltmVirtualServEntry 16 }

ltmVirtualServLasthopPoolName OBJECT-TYPE
	SYNTAX LongDisplayString
	MAX-ACCESS read-only
	STATUS current
	DESCRIPTION
		"The last hop pool for the specified virtual server if traffic is
		 transparent."
	::= { ltmVirtualServEntry 17 }

ltmVirtualServSnatpoolName OBJECT-TYPE
	SYNTAX LongDisplayString
	MAX-ACCESS read-only
	STATUS	 deprecated
	DESCRIPTION
		"Deprecated! No longer a direct attribute of the virtual server.
	       The name of a SNAT pool used by the specified virtual server."
	::= { ltmVirtualServEntry 18 }

ltmVirtualServDefaultPool OBJECT-TYPE
	SYNTAX LongDisplayString
	MAX-ACCESS read-only
	STATUS current
	DESCRIPTION
		"The name of a default pool used by the specified virtual server."
	::= { ltmVirtualServEntry 19 }

ltmVirtualServFallbackPersist OBJECT-TYPE
	SYNTAX LongDisplayString
	MAX-ACCESS read-only
	STATUS current
	DESCRIPTION
		"The persist profile name to use for fallback by the specified virtual server."
	::= { ltmVirtualServEntry 20 }

ltmVirtualServActualPvaAccel OBJECT-TYPE
	SYNTAX INTEGER {
		full(0),
		partial(1),
		none(2)
	}
	MAX-ACCESS read-only
	STATUS current
	DESCRIPTION
		"The actual hardware acceleration mode for the specified virtual server."
	::= { ltmVirtualServEntry 21 }

ltmVirtualServAvailabilityState OBJECT-TYPE
	SYNTAX INTEGER {
		none(0),
		green(1),
		yellow(2),
		red(3),
		blue(4)
	}
	MAX-ACCESS read-only
	STATUS	 deprecated
	DESCRIPTION
		"Deprecated!
		Replaced by ltmVsServStatusAvailState under ltmVirtualServStatus.
		The state of the specified virtual server availability indicated in color."
	::= { ltmVirtualServEntry 22 }

ltmVirtualServEnabledState OBJECT-TYPE
	SYNTAX INTEGER {
		none(0),
		enabled(1),
		disabled(2),
		disabledbyparent(3)
	}
	MAX-ACCESS read-only
	STATUS	 deprecated
	DESCRIPTION
		"Deprecated!
		Replaced by ltmVsServStatusEnabledState under ltmVirtualServStatus.
		The state of the specified virtual server activity status, as specified
		by the user."
	::= { ltmVirtualServEntry 23 }

ltmVirtualServDisabledParentType OBJECT-TYPE
	SYNTAX Gauge
	MAX-ACCESS read-only
	STATUS	 deprecated
	DESCRIPTION
		"Deprecated!
		Replaced by ltmVsServStatusParentType under ltmVirtualServStatus.
		The type of parent object which disabled the specified virtual server."
	::= { ltmVirtualServEntry 24 }

ltmVirtualServStatusReason OBJECT-TYPE
	SYNTAX LongDisplayString
	MAX-ACCESS read-only
	STATUS	 deprecated
	DESCRIPTION
		"Deprecated!
		Replaced by ltmVsServStatusDetailReason under ltmVirtualServStatus.
		The detail description of the node's status of parent object
		which disabled the specified virtual server."
	::= { ltmVirtualServEntry 25 }

ltmVirtualServGtmScore OBJECT-TYPE
	SYNTAX Gauge
	MAX-ACCESS read-only
	STATUS current
	DESCRIPTION
		"A user-defined value that specifies the ranking of the virtual server
		when compared to other virtual servers within the same pool"
	::= { ltmVirtualServEntry 26 }

ltmVirtualServCmpEnabled OBJECT-TYPE
	SYNTAX INTEGER {
		false(0),
		true(1)
	}
	MAX-ACCESS read-only
	STATUS current
	DESCRIPTION
		"The state indicating whether CMP (Cluster Multiple Processor) is enabled or not for the specified virtual server."
	::= { ltmVirtualServEntry 27 }

ltmVirtualServSrcport OBJECT-TYPE
	SYNTAX INTEGER {
		srcportreserve(0),
		srcportreservestrict(1),
		srcportchange(2)
	}
	MAX-ACCESS read-only
	STATUS current
	DESCRIPTION
		"The srcport type.
	        srcportreserve       - The srcport reserved;
	        srcportreservestrict - The srcport reserved strict;
	        srcportchange        - The srcport changed;"
	::= { ltmVirtualServEntry 28 }

ltmVirtualServVaName OBJECT-TYPE
	SYNTAX LongDisplayString
	MAX-ACCESS read-only
	STATUS current
	DESCRIPTION
		"virtual address name."
	::= { ltmVirtualServEntry 29 }

ltmVirtualServSourceAddressTranslationType OBJECT-TYPE
	SYNTAX INTEGER {
		none(0),
		snat(1),
		lsn(2),
		automap(3)
	}
	MAX-ACCESS read-only
	STATUS current
	DESCRIPTION
		"The type of Source Address Translation associated with the specified virtual server.
		none - No Source Address Translation used by the virtual server;
		snat - The Source Address Translation uses a SNAT pool of translation addresses;
		lsn - The Source Address Translation uses an LSN pool of translation addresses;
		automap - The Source Address Translation uses self IP addresses."
	::= { ltmVirtualServEntry 30 }

ltmVirtualServSourceAddressTranslationPool OBJECT-TYPE
	SYNTAX LongDisplayString
	MAX-ACCESS read-only
	STATUS current
	DESCRIPTION
		"The name of a LSN Source Address Translation pool used by the specified virtual server."
	::= { ltmVirtualServEntry 31 }

ltmVirtualServServiceDownImmediateAction OBJECT-TYPE
	SYNTAX INTEGER {
		none(0),
		reset(1),
		drop(2)
	}
	MAX-ACCESS read-only
	STATUS current
	DESCRIPTION
		"Specifies the immediate action to take upon the receipt of the initial client's
		SYN packet if the availability status of the virtual server is Offline or Unavailable.
		This is supported for the virtual server of Standard type and TCP protocol.
		none - BIG-IP system takes no immediate action;
		reset - BIG-IP system immediately resets the newly arriving connections destined for the
		        virtual server IP address and sends a TCP reset (RST) message;
		drop - BIG-IP system immediately drops the newly arriving connections destined for the
		        virtual server IP address."
	::= { ltmVirtualServEntry 32 }

ltmVirtualServServersslUseSni OBJECT-TYPE
	SYNTAX INTEGER {
		false(0),
		true(1)
	}
	MAX-ACCESS read-only
	STATUS current
	DESCRIPTION
		"The state indicating whether the server-ssl profile is selected based on the SNI in the ClientHello."
	::= { ltmVirtualServEntry 33 }

--==================================================================
-- Virtual_server_stat
--==================================================================
ltmVirtualServStatResetStats OBJECT-TYPE
	SYNTAX INTEGER
	MAX-ACCESS read-write
	STATUS current
	DESCRIPTION
		"The action to reset resettable statistics data in ltmVirtualServStat.
		 Setting this value to 1 will reset statistics data.
		 Note, some statistics data may not be reset including data that are incremental counters."
	::= { ltmVirtualServStat 1 }

ltmVirtualServStatNumber OBJECT-TYPE
	SYNTAX INTEGER
	MAX-ACCESS read-only
	STATUS current
	DESCRIPTION
		"The number of ltmVirtualServStat entries in the table."
	::= { ltmVirtualServStat 2 }

ltmVirtualServStatTable OBJECT-TYPE
	SYNTAX SEQUENCE OF LtmVirtualServStatEntry
	MAX-ACCESS not-accessible
	STATUS current
	DESCRIPTION
		"A table containing statistic information of virtual servers."
	::= { ltmVirtualServStat 3 }

ltmVirtualServStatEntry OBJECT-TYPE
	SYNTAX  LtmVirtualServStatEntry
	MAX-ACCESS not-accessible
	STATUS current
	DESCRIPTION
		"Columns in the ltmVirtualServStat Table"
	INDEX {
		ltmVirtualServStatName
	}
	::= { ltmVirtualServStatTable 1 }

LtmVirtualServStatEntry ::=
	SEQUENCE {
        	ltmVirtualServStatName                                    LongDisplayString,
        	ltmVirtualServStatCsMinConnDur                            Counter64,
        	ltmVirtualServStatCsMaxConnDur                            Counter64,
        	ltmVirtualServStatCsMeanConnDur                           Counter64,
        	ltmVirtualServStatNoNodesErrors                           Counter64,
        	ltmVirtualServStatClientPktsIn                            Counter64,
        	ltmVirtualServStatClientBytesIn                           Counter64,
        	ltmVirtualServStatClientPktsOut                           Counter64,
        	ltmVirtualServStatClientBytesOut                          Counter64,
        	ltmVirtualServStatClientMaxConns                          Counter64,
        	ltmVirtualServStatClientTotConns                          Counter64,
        	ltmVirtualServStatClientCurConns                          Gauge,
        	ltmVirtualServStatEphemeralPktsIn                         Counter64,
        	ltmVirtualServStatEphemeralBytesIn                        Counter64,
        	ltmVirtualServStatEphemeralPktsOut                        Counter64,
        	ltmVirtualServStatEphemeralBytesOut                       Counter64,
        	ltmVirtualServStatEphemeralMaxConns                       Counter64,
        	ltmVirtualServStatEphemeralTotConns                       Counter64,
        	ltmVirtualServStatEphemeralCurConns                       Gauge,
        	ltmVirtualServStatPvaPktsIn                               Counter64,
        	ltmVirtualServStatPvaBytesIn                              Counter64,
        	ltmVirtualServStatPvaPktsOut                              Counter64,
        	ltmVirtualServStatPvaBytesOut                             Counter64,
        	ltmVirtualServStatPvaMaxConns                             Counter64,
        	ltmVirtualServStatPvaTotConns                             Counter64,
        	ltmVirtualServStatPvaCurConns                             Gauge,
        	ltmVirtualServStatTotRequests                             Counter64,
        	ltmVirtualServStatTotPvaAssistConn                        Counter64,
        	ltmVirtualServStatCurrPvaAssistConn                       Gauge,
        	ltmVirtualServStatCycleCount                              Counter64,
        	ltmVirtualServStatVsUsageRatio5s                          Gauge,
        	ltmVirtualServStatVsUsageRatio1m                          Gauge,
        	ltmVirtualServStatVsUsageRatio5m                          Gauge,
        	ltmVirtualServStatCurrentConnsPerSec                      Gauge,
        	ltmVirtualServStatDurationRateExceeded                    Gauge,
        	ltmVirtualServStatSwSyncookies                            Counter64,
        	ltmVirtualServStatSwSyncookieAccepts                      Counter64,
        	ltmVirtualServStatHwSyncookies                            Counter64,
        	ltmVirtualServStatHwSyncookieAccepts                      Counter64,
        	ltmVirtualServStatClientEvictedConns                      Counter64,
        	ltmVirtualServStatClientSlowKilled                        Counter64,
        	ltmVirtualServStatWlSyncookieHits                         Counter64,
        	ltmVirtualServStatWlSyncookieAccepts                      Counter64,
        	ltmVirtualServStatWlSyncookieRejects                      Counter64,
        	ltmVirtualServStatMsgMrIn                                 Counter64,
        	ltmVirtualServStatMsgMrOut                                Counter64,
        	ltmVirtualServStatReqMrIn                                 Counter64,
        	ltmVirtualServStatReqMrOut                                Counter64,
        	ltmVirtualServStatRespMrIn                                Counter64,
        	ltmVirtualServStatRespMrOut                               Counter64
	}

ltmVirtualServStatName OBJECT-TYPE
	SYNTAX LongDisplayString
	MAX-ACCESS read-only
	STATUS current
	DESCRIPTION
		"The name of a virtual server."
	::= { ltmVirtualServStatEntry 1 }

ltmVirtualServStatCsMinConnDur OBJECT-TYPE
	SYNTAX Counter64
	MAX-ACCESS read-only
	STATUS current
	DESCRIPTION
		"The minimum connection duration in milliseconds among all connections
		through the specified virtual server."
	::= { ltmVirtualServStatEntry 2 }

ltmVirtualServStatCsMaxConnDur OBJECT-TYPE
	SYNTAX Counter64
	MAX-ACCESS read-only
	STATUS current
	DESCRIPTION
		"The maximum connection duration in milliseconds among all connections
		through the specified virtual server."
	::= { ltmVirtualServStatEntry 3 }

ltmVirtualServStatCsMeanConnDur OBJECT-TYPE
	SYNTAX Counter64
	MAX-ACCESS read-only
	STATUS current
	DESCRIPTION
		"The average connection duration in milliseconds for all connections
		through the specified virtual server."
	::= { ltmVirtualServStatEntry 4 }

ltmVirtualServStatNoNodesErrors OBJECT-TYPE
	SYNTAX Counter64
	MAX-ACCESS read-only
	STATUS current
	DESCRIPTION
		"The number of no-node errors. If active server node is zero,
	         this counter is incremented."
	::= { ltmVirtualServStatEntry 5 }

ltmVirtualServStatClientPktsIn OBJECT-TYPE
	SYNTAX Counter64
	MAX-ACCESS read-only
	STATUS current
	DESCRIPTION
		"The number of packets received by the specified virtual server from client-side."
	::= { ltmVirtualServStatEntry 6 }

ltmVirtualServStatClientBytesIn OBJECT-TYPE
	SYNTAX Counter64
	MAX-ACCESS read-only
	STATUS current
	DESCRIPTION
		"The number of bytes received by the specified virtual server from client-side."
	::= { ltmVirtualServStatEntry 7 }

ltmVirtualServStatClientPktsOut OBJECT-TYPE
	SYNTAX Counter64
	MAX-ACCESS read-only
	STATUS current
	DESCRIPTION
		"The number of packets sent to client-side from the specified virtual server."
	::= { ltmVirtualServStatEntry 8 }

ltmVirtualServStatClientBytesOut OBJECT-TYPE
	SYNTAX Counter64
	MAX-ACCESS read-only
	STATUS current
	DESCRIPTION
		"The number of bytes sent to client-side from the specified virtual server."
	::= { ltmVirtualServStatEntry 9 }

ltmVirtualServStatClientMaxConns OBJECT-TYPE
	SYNTAX Counter64
	MAX-ACCESS read-only
	STATUS current
	DESCRIPTION
		"The maximum connections from client-side to the specified virtual server."
	::= { ltmVirtualServStatEntry 10 }

ltmVirtualServStatClientTotConns OBJECT-TYPE
	SYNTAX Counter64
	MAX-ACCESS read-only
	STATUS current
	DESCRIPTION
		"The total connections from client-side to the specified virtual server."
	::= { ltmVirtualServStatEntry 11 }

ltmVirtualServStatClientCurConns OBJECT-TYPE
	SYNTAX Gauge
	MAX-ACCESS read-only
	STATUS current
	DESCRIPTION
		"The current connections from client-side to the specified virtual server."
	::= { ltmVirtualServStatEntry 12 }

ltmVirtualServStatEphemeralPktsIn OBJECT-TYPE
	SYNTAX Counter64
	MAX-ACCESS read-only
	STATUS current
	DESCRIPTION
		"The number of packets received ephemeral by the specified virtual server."
	::= { ltmVirtualServStatEntry 13 }

ltmVirtualServStatEphemeralBytesIn OBJECT-TYPE
	SYNTAX Counter64
	MAX-ACCESS read-only
	STATUS current
	DESCRIPTION
		"The number of bytes received ephemeral by the specified virtual server."
	::= { ltmVirtualServStatEntry 14 }

ltmVirtualServStatEphemeralPktsOut OBJECT-TYPE
	SYNTAX Counter64
	MAX-ACCESS read-only
	STATUS current
	DESCRIPTION
		"The number of packets transmitted ephemeral from the specified virtual server."
	::= { ltmVirtualServStatEntry 15 }

ltmVirtualServStatEphemeralBytesOut OBJECT-TYPE
	SYNTAX Counter64
	MAX-ACCESS read-only
	STATUS current
	DESCRIPTION
		"The number of bytes transmitted ephemeral from the specified virtual server."
	::= { ltmVirtualServStatEntry 16 }

ltmVirtualServStatEphemeralMaxConns OBJECT-TYPE
	SYNTAX Counter64
	MAX-ACCESS read-only
	STATUS current
	DESCRIPTION
		"The maximum ephemeral connections to the specified virtual server."
	::= { ltmVirtualServStatEntry 17 }

ltmVirtualServStatEphemeralTotConns OBJECT-TYPE
	SYNTAX Counter64
	MAX-ACCESS read-only
	STATUS current
	DESCRIPTION
		"The total ephemeral connections to the specified virtual server."
	::= { ltmVirtualServStatEntry 18 }

ltmVirtualServStatEphemeralCurConns OBJECT-TYPE
	SYNTAX Gauge
	MAX-ACCESS read-only
	STATUS current
	DESCRIPTION
		"The current ephemeral connections to the specified virtual server."
	::= { ltmVirtualServStatEntry 19 }

ltmVirtualServStatPvaPktsIn OBJECT-TYPE
	SYNTAX Counter64
	MAX-ACCESS read-only
	STATUS current
	DESCRIPTION
		"The total number of hardware accelerated packets received by the specified virtual server."
	::= { ltmVirtualServStatEntry 20 }

ltmVirtualServStatPvaBytesIn OBJECT-TYPE
	SYNTAX Counter64
	MAX-ACCESS read-only
	STATUS current
	DESCRIPTION
		"The total number of hardware accelerated bytes received by the specified virtual server."
	::= { ltmVirtualServStatEntry 21 }

ltmVirtualServStatPvaPktsOut OBJECT-TYPE
	SYNTAX Counter64
	MAX-ACCESS read-only
	STATUS current
	DESCRIPTION
		"The total number of hardware accelerated packets sent out from the specified virtual server."
	::= { ltmVirtualServStatEntry 22 }

ltmVirtualServStatPvaBytesOut OBJECT-TYPE
	SYNTAX Counter64
	MAX-ACCESS read-only
	STATUS current
	DESCRIPTION
		"The total number of hardware accelerated bytes sent out from the specified virtual server."
	::= { ltmVirtualServStatEntry 23 }

ltmVirtualServStatPvaMaxConns OBJECT-TYPE
	SYNTAX Counter64
	MAX-ACCESS read-only
	STATUS current
	DESCRIPTION
		"The maximum hardware accelerated connections to the specified virtual server."
	::= { ltmVirtualServStatEntry 24 }

ltmVirtualServStatPvaTotConns OBJECT-TYPE
	SYNTAX Counter64
	MAX-ACCESS read-only
	STATUS current
	DESCRIPTION
		"The total hardware accelerated connections to the specified virtual server."
	::= { ltmVirtualServStatEntry 25 }

ltmVirtualServStatPvaCurConns OBJECT-TYPE
	SYNTAX Gauge
	MAX-ACCESS read-only
	STATUS current
	DESCRIPTION
		"The current hardware accelerated connections to the specified virtual server."
	::= { ltmVirtualServStatEntry 26 }

ltmVirtualServStatTotRequests OBJECT-TYPE
	SYNTAX Counter64
	MAX-ACCESS read-only
	STATUS current
	DESCRIPTION
		"The total number of requests going through the specified virtual server."
	::= { ltmVirtualServStatEntry 27 }

ltmVirtualServStatTotPvaAssistConn OBJECT-TYPE
	SYNTAX Counter64
	MAX-ACCESS read-only
	STATUS current
	DESCRIPTION
		"The total number of connections to the specified virtual server, which
		are partially hardware accelerated."
	::= { ltmVirtualServStatEntry 28 }

ltmVirtualServStatCurrPvaAssistConn OBJECT-TYPE
	SYNTAX Gauge
	MAX-ACCESS read-only
	STATUS current
	DESCRIPTION
		"The current number of connections to the specified virtual server, which
		are partially hardware accelerated."
	::= { ltmVirtualServStatEntry 29 }

ltmVirtualServStatCycleCount OBJECT-TYPE
	SYNTAX Counter64
	MAX-ACCESS read-only
	STATUS current
	DESCRIPTION
		"CPU cycle count since last system restart."
	::= { ltmVirtualServStatEntry 30 }

ltmVirtualServStatVsUsageRatio5s OBJECT-TYPE
	SYNTAX Gauge
	MAX-ACCESS read-only
	STATUS current
	DESCRIPTION
		"The percentage of time Virtual Server was busy over the last 5 seconds."
	::= { ltmVirtualServStatEntry 31 }

ltmVirtualServStatVsUsageRatio1m OBJECT-TYPE
	SYNTAX Gauge
	MAX-ACCESS read-only
	STATUS current
	DESCRIPTION
		"The percentage of time Virtual Server was busy over the last 1 minute."
	::= { ltmVirtualServStatEntry 32 }

ltmVirtualServStatVsUsageRatio5m OBJECT-TYPE
	SYNTAX Gauge
	MAX-ACCESS read-only
	STATUS current
	DESCRIPTION
		"The percentage of time Virtual Server was busy over the last 5 minutes."
	::= { ltmVirtualServStatEntry 33 }

ltmVirtualServStatCurrentConnsPerSec OBJECT-TYPE
	SYNTAX Gauge
	MAX-ACCESS read-only
	STATUS current
	DESCRIPTION
		"The last recorded value for the number of connections to the virtual server when connections hit a rate limit; this calculation is only maintained if rate limiting is configured for the service."
	::= { ltmVirtualServStatEntry 34 }

ltmVirtualServStatDurationRateExceeded OBJECT-TYPE
	SYNTAX Gauge
	MAX-ACCESS read-only
	STATUS current
	DESCRIPTION
		"Duration of time in seconds the specified virtual server has exceeded the
		configured connection rate limit."
	::= { ltmVirtualServStatEntry 35 }

ltmVirtualServStatSwSyncookies OBJECT-TYPE
	SYNTAX Counter64
	MAX-ACCESS read-only
	STATUS current
	DESCRIPTION
		"The number of syn cookies received."
	::= { ltmVirtualServStatEntry 36 }

ltmVirtualServStatSwSyncookieAccepts OBJECT-TYPE
	SYNTAX Counter64
	MAX-ACCESS read-only
	STATUS current
	DESCRIPTION
		"The number of syn cookies received that were accepted."
	::= { ltmVirtualServStatEntry 37 }

ltmVirtualServStatHwSyncookies OBJECT-TYPE
	SYNTAX Counter64
	MAX-ACCESS read-only
	STATUS current
	DESCRIPTION
		"The number of hardware syn cookies received."
	::= { ltmVirtualServStatEntry 38 }

ltmVirtualServStatHwSyncookieAccepts OBJECT-TYPE
	SYNTAX Counter64
	MAX-ACCESS read-only
	STATUS current
	DESCRIPTION
		"The number of hardware syn cookies received that were accepted."
	::= { ltmVirtualServStatEntry 39 }

ltmVirtualServStatClientEvictedConns OBJECT-TYPE
	SYNTAX Counter64
	MAX-ACCESS read-only
	STATUS current
	DESCRIPTION
		"The number of client-side connections that have been evicted on the specified virtual server."
	::= { ltmVirtualServStatEntry 40 }

ltmVirtualServStatClientSlowKilled OBJECT-TYPE
	SYNTAX Counter64
	MAX-ACCESS read-only
	STATUS current
	DESCRIPTION
		"The number of slow client-side connections that have been killed on the specified virtual server."
	::= { ltmVirtualServStatEntry 41 }

ltmVirtualServStatWlSyncookieHits OBJECT-TYPE
	SYNTAX Counter64
	MAX-ACCESS read-only
	STATUS current
	DESCRIPTION
		"The number of whitelist syn cookie hits."
	::= { ltmVirtualServStatEntry 42 }

ltmVirtualServStatWlSyncookieAccepts OBJECT-TYPE
	SYNTAX Counter64
	MAX-ACCESS read-only
	STATUS current
	DESCRIPTION
		"The number of whitelist syn cookies received that were accepted."
	::= { ltmVirtualServStatEntry 43 }

ltmVirtualServStatWlSyncookieRejects OBJECT-TYPE
	SYNTAX Counter64
	MAX-ACCESS read-only
	STATUS current
	DESCRIPTION
		"The number of whitelist syn cookies received that were rejected."
	::= { ltmVirtualServStatEntry 44 }

ltmVirtualServStatMsgMrIn OBJECT-TYPE
	SYNTAX Counter64
	MAX-ACCESS read-only
	STATUS current
	DESCRIPTION
		"The number of incoming routed messages for specified virtual server."
	::= { ltmVirtualServStatEntry 45 }

ltmVirtualServStatMsgMrOut OBJECT-TYPE
	SYNTAX Counter64
	MAX-ACCESS read-only
	STATUS current
	DESCRIPTION
		"The number of outgoing routed messages for specified virtual server."
	::= { ltmVirtualServStatEntry 46 }

ltmVirtualServStatReqMrIn OBJECT-TYPE
	SYNTAX Counter64
	MAX-ACCESS read-only
	STATUS current
	DESCRIPTION
		"The number of incoming requests routed messages for specified virtual server."
	::= { ltmVirtualServStatEntry 47 }

ltmVirtualServStatReqMrOut OBJECT-TYPE
	SYNTAX Counter64
	MAX-ACCESS read-only
	STATUS current
	DESCRIPTION
		"The number of outgoing requests routed messages for specified virtual server."
	::= { ltmVirtualServStatEntry 48 }

ltmVirtualServStatRespMrIn OBJECT-TYPE
	SYNTAX Counter64
	MAX-ACCESS read-only
	STATUS current
	DESCRIPTION
		"The number of incoming responces routed messages for specified virtual server."
	::= { ltmVirtualServStatEntry 49 }

ltmVirtualServStatRespMrOut OBJECT-TYPE
	SYNTAX Counter64
	MAX-ACCESS read-only
	STATUS current
	DESCRIPTION
		"The number of incoming responces routed messages for specified virtual server."
	::= { ltmVirtualServStatEntry 50 }

--==================================================================
-- Virtual_server_auth
--==================================================================
ltmVirtualServAuthNumber OBJECT-TYPE
	SYNTAX INTEGER
	MAX-ACCESS read-only
	STATUS current
	DESCRIPTION
		"The number of ltmVirtualServAuth entries in the table."
	::= { ltmVirtualServAuth 1 }

ltmVirtualServAuthTable OBJECT-TYPE
	SYNTAX SEQUENCE OF LtmVirtualServAuthEntry
	MAX-ACCESS not-accessible
	STATUS current
	DESCRIPTION
		"A table containing information of virtual server auth profiles."
	::= { ltmVirtualServAuth 2 }

ltmVirtualServAuthEntry OBJECT-TYPE
	SYNTAX  LtmVirtualServAuthEntry
	MAX-ACCESS not-accessible
	STATUS current
	DESCRIPTION
		"Columns in the ltmVirtualServAuth Table"
	INDEX {
		ltmVirtualServAuthVsName,
		ltmVirtualServAuthProfileName
	}
	::= { ltmVirtualServAuthTable 1 }

LtmVirtualServAuthEntry ::=
	SEQUENCE {
        	ltmVirtualServAuthVsName                                  LongDisplayString,
        	ltmVirtualServAuthProfileName                             LongDisplayString
	}

ltmVirtualServAuthVsName OBJECT-TYPE
	SYNTAX LongDisplayString
	MAX-ACCESS read-only
	STATUS current
	DESCRIPTION
		"The name of a virtual server."
	::= { ltmVirtualServAuthEntry 1 }

ltmVirtualServAuthProfileName OBJECT-TYPE
	SYNTAX LongDisplayString
	MAX-ACCESS read-only
	STATUS current
	DESCRIPTION
		"The name of an auth profile associated with the specified virtual server."
	::= { ltmVirtualServAuthEntry 2 }

--==================================================================
-- Virtual_server_persist
--==================================================================
ltmVirtualServPersistNumber OBJECT-TYPE
	SYNTAX INTEGER
	MAX-ACCESS read-only
	STATUS current
	DESCRIPTION
		"The number of ltmVirtualServPersist entries in the table."
	::= { ltmVirtualServPersist 1 }

ltmVirtualServPersistTable OBJECT-TYPE
	SYNTAX SEQUENCE OF LtmVirtualServPersistEntry
	MAX-ACCESS not-accessible
	STATUS current
	DESCRIPTION
		"A table containing information of virtual server persistence profiles."
	::= { ltmVirtualServPersist 2 }

ltmVirtualServPersistEntry OBJECT-TYPE
	SYNTAX  LtmVirtualServPersistEntry
	MAX-ACCESS not-accessible
	STATUS current
	DESCRIPTION
		"Columns in the ltmVirtualServPersist Table"
	INDEX {
		ltmVirtualServPersistVsName,
		ltmVirtualServPersistProfileName
	}
	::= { ltmVirtualServPersistTable 1 }

LtmVirtualServPersistEntry ::=
	SEQUENCE {
        	ltmVirtualServPersistVsName                               LongDisplayString,
        	ltmVirtualServPersistProfileName                          LongDisplayString,
        	ltmVirtualServPersistUseDefault                           INTEGER
	}

ltmVirtualServPersistVsName OBJECT-TYPE
	SYNTAX LongDisplayString
	MAX-ACCESS read-only
	STATUS current
	DESCRIPTION
		"The name of a virtual server."
	::= { ltmVirtualServPersistEntry 1 }

ltmVirtualServPersistProfileName OBJECT-TYPE
	SYNTAX LongDisplayString
	MAX-ACCESS read-only
	STATUS current
	DESCRIPTION
		"The name of a persist profile associated with the specified virtual server."
	::= { ltmVirtualServPersistEntry 2 }

ltmVirtualServPersistUseDefault OBJECT-TYPE
	SYNTAX INTEGER {
		false(0),
		true(1)
	}
	MAX-ACCESS read-only
	STATUS current
	DESCRIPTION
		"The persist profile is to be used if a rule does not
		select a persist type."
	::= { ltmVirtualServPersistEntry 3 }

--==================================================================
-- Virtual_server_profile
--==================================================================
ltmVirtualServProfileNumber OBJECT-TYPE
	SYNTAX INTEGER
	MAX-ACCESS read-only
	STATUS current
	DESCRIPTION
		"The number of ltmVirtualServProfile entries in the table."
	::= { ltmVirtualServProfile 1 }

ltmVirtualServProfileTable OBJECT-TYPE
	SYNTAX SEQUENCE OF LtmVirtualServProfileEntry
	MAX-ACCESS not-accessible
	STATUS current
	DESCRIPTION
		"A table containing information of virtual server profiles."
	::= { ltmVirtualServProfile 2 }

ltmVirtualServProfileEntry OBJECT-TYPE
	SYNTAX  LtmVirtualServProfileEntry
	MAX-ACCESS not-accessible
	STATUS current
	DESCRIPTION
		"Columns in the ltmVirtualServProfile Table"
	INDEX {
		ltmVirtualServProfileVsName,
		ltmVirtualServProfileProfileName
	}
	::= { ltmVirtualServProfileTable 1 }

LtmVirtualServProfileEntry ::=
	SEQUENCE {
        	ltmVirtualServProfileVsName                               LongDisplayString,
        	ltmVirtualServProfileProfileName                          LongDisplayString,
        	ltmVirtualServProfileType                                 INTEGER,
        	ltmVirtualServProfileContext                              INTEGER
	}

ltmVirtualServProfileVsName OBJECT-TYPE
	SYNTAX LongDisplayString
	MAX-ACCESS read-only
	STATUS current
	DESCRIPTION
		"The name of a virtual server."
	::= { ltmVirtualServProfileEntry 1 }

ltmVirtualServProfileProfileName OBJECT-TYPE
	SYNTAX LongDisplayString
	MAX-ACCESS read-only
	STATUS current
	DESCRIPTION
		"The name of a profile associated with the specified virtual server."
	::= { ltmVirtualServProfileEntry 2 }

ltmVirtualServProfileType OBJECT-TYPE
	SYNTAX INTEGER {
		auth(0),
		http(1),
		serverssl(2),
		clientssl(3),
		fastl4(4),
		tcp(5),
		udp(6),
		ftp(7),
		persist(8),
		connpool(9),
		stream(10),
		xml(11),
		fasthttp(12),
		iiop(13),
		rtsp(14),
		user(15),
		httpclass(16),
		dns(17),
		sctp(18),
		instance(19),
		sipp(20),
		dos(21),
		pptp(62)
	}
	MAX-ACCESS read-only
	STATUS current
	DESCRIPTION
		"The type of the profile used by the specified virtual server."
	::= { ltmVirtualServProfileEntry 3 }

ltmVirtualServProfileContext OBJECT-TYPE
	SYNTAX INTEGER {
		all(0),
		client(1),
		server(2)
	}
	MAX-ACCESS read-only
	STATUS current
	DESCRIPTION
		"This is used to determine which side of the proxy a protocol
		type profile (specifically  TCP/UDP) is applied to.
		none   - for profiles that don't need any context;
		all    - profile applies to both client and server;
		client - profile applies to the client-side;
		server - profile applies to the server-side."
	::= { ltmVirtualServProfileEntry 4 }

--==================================================================
-- Virtual_server_pool
--==================================================================
ltmVirtualServPoolNumber OBJECT-TYPE
	SYNTAX INTEGER
	MAX-ACCESS read-only
	STATUS current
	DESCRIPTION
		"The number of ltmVirtualServPool entries in the table."
	::= { ltmVirtualServPool 1 }

ltmVirtualServPoolTable OBJECT-TYPE
	SYNTAX SEQUENCE OF LtmVirtualServPoolEntry
	MAX-ACCESS not-accessible
	STATUS current
	DESCRIPTION
		"A table containing information of non-default pools related to virtual servers."
	::= { ltmVirtualServPool 2 }

ltmVirtualServPoolEntry OBJECT-TYPE
	SYNTAX  LtmVirtualServPoolEntry
	MAX-ACCESS not-accessible
	STATUS current
	DESCRIPTION
		"Columns in the ltmVirtualServPool Table"
	INDEX {
		ltmVirtualServPoolVirtualServerName,
		ltmVirtualServPoolPoolName
	}
	::= { ltmVirtualServPoolTable 1 }

LtmVirtualServPoolEntry ::=
	SEQUENCE {
        	ltmVirtualServPoolVirtualServerName                       LongDisplayString,
        	ltmVirtualServPoolPoolName                                LongDisplayString,
        	ltmVirtualServPoolRuleName                                LongDisplayString
	}

ltmVirtualServPoolVirtualServerName OBJECT-TYPE
	SYNTAX LongDisplayString
	MAX-ACCESS read-only
	STATUS current
	DESCRIPTION
		"The name of a virtual server."
	::= { ltmVirtualServPoolEntry 1 }

ltmVirtualServPoolPoolName OBJECT-TYPE
	SYNTAX LongDisplayString
	MAX-ACCESS read-only
	STATUS current
	DESCRIPTION
		"The name of a non-default pool that the specified virtual server is referencing."
	::= { ltmVirtualServPoolEntry 2 }

ltmVirtualServPoolRuleName OBJECT-TYPE
	SYNTAX LongDisplayString
	MAX-ACCESS read-only
	STATUS current
	DESCRIPTION
		"The name of a rule that the specified virtual server is referencing.
		This is for future use and has not been supported in current version."
	::= { ltmVirtualServPoolEntry 3 }

--==================================================================
-- Virtual_server_clone_pool
--==================================================================
ltmVirtualServClonePoolNumber OBJECT-TYPE
	SYNTAX INTEGER
	MAX-ACCESS read-only
	STATUS current
	DESCRIPTION
		"The number of ltmVirtualServClonePool entries in the table."
	::= { ltmVirtualServClonePool 1 }

ltmVirtualServClonePoolTable OBJECT-TYPE
	SYNTAX SEQUENCE OF LtmVirtualServClonePoolEntry
	MAX-ACCESS not-accessible
	STATUS current
	DESCRIPTION
		"A table containing information of pools related to virtual servers."
	::= { ltmVirtualServClonePool 2 }

ltmVirtualServClonePoolEntry OBJECT-TYPE
	SYNTAX  LtmVirtualServClonePoolEntry
	MAX-ACCESS not-accessible
	STATUS current
	DESCRIPTION
		"Columns in the ltmVirtualServClonePool Table"
	INDEX {
		ltmVirtualServClonePoolVirtualServerName,
		ltmVirtualServClonePoolPoolName,
		ltmVirtualServClonePoolType
	}
	::= { ltmVirtualServClonePoolTable 1 }

LtmVirtualServClonePoolEntry ::=
	SEQUENCE {
        	ltmVirtualServClonePoolVirtualServerName                  LongDisplayString,
        	ltmVirtualServClonePoolPoolName                           LongDisplayString,
        	ltmVirtualServClonePoolType                               INTEGER
	}

ltmVirtualServClonePoolVirtualServerName OBJECT-TYPE
	SYNTAX LongDisplayString
	MAX-ACCESS read-only
	STATUS current
	DESCRIPTION
		"The name of a virtual server."
	::= { ltmVirtualServClonePoolEntry 1 }

ltmVirtualServClonePoolPoolName OBJECT-TYPE
	SYNTAX LongDisplayString
	MAX-ACCESS read-only
	STATUS current
	DESCRIPTION
		"The name of a clone pool associated with the specified virtual server."
	::= { ltmVirtualServClonePoolEntry 2 }

ltmVirtualServClonePoolType OBJECT-TYPE
	SYNTAX INTEGER {
		unspec(0),
		clientside(1),
		serverside(2)
	}
	MAX-ACCESS read-only
	STATUS current
	DESCRIPTION
		"The type of the clone pool associated with the specified virtual server."
	::= { ltmVirtualServClonePoolEntry 3 }

--==================================================================
-- Virtual_server_rule
--==================================================================
ltmVirtualServRuleNumber OBJECT-TYPE
	SYNTAX INTEGER
	MAX-ACCESS read-only
	STATUS current
	DESCRIPTION
		"The number of ltmVirtualServRule entries in the table."
	::= { ltmVirtualServRule 1 }

ltmVirtualServRuleTable OBJECT-TYPE
	SYNTAX SEQUENCE OF LtmVirtualServRuleEntry
	MAX-ACCESS not-accessible
	STATUS current
	DESCRIPTION
		"A table containing information of rules related to virtual servers."
	::= { ltmVirtualServRule 2 }

ltmVirtualServRuleEntry OBJECT-TYPE
	SYNTAX  LtmVirtualServRuleEntry
	MAX-ACCESS not-accessible
	STATUS current
	DESCRIPTION
		"Columns in the ltmVirtualServRule Table"
	INDEX {
		ltmVirtualServRuleVirtualServerName,
		ltmVirtualServRuleRuleName
	}
	::= { ltmVirtualServRuleTable 1 }

LtmVirtualServRuleEntry ::=
	SEQUENCE {
        	ltmVirtualServRuleVirtualServerName                       LongDisplayString,
        	ltmVirtualServRuleRuleName                                LongDisplayString,
        	ltmVirtualServRulePriority                                INTEGER
	}

ltmVirtualServRuleVirtualServerName OBJECT-TYPE
	SYNTAX LongDisplayString
	MAX-ACCESS read-only
	STATUS current
	DESCRIPTION
		"The name of a virtual server."
	::= { ltmVirtualServRuleEntry 1 }

ltmVirtualServRuleRuleName OBJECT-TYPE
	SYNTAX LongDisplayString
	MAX-ACCESS read-only
	STATUS current
	DESCRIPTION
		"The name of a rule associated with the specified virtual server."
	::= { ltmVirtualServRuleEntry 2 }

ltmVirtualServRulePriority OBJECT-TYPE
	SYNTAX INTEGER
	MAX-ACCESS read-only
	STATUS current
	DESCRIPTION
		"The priority of the rule among rules used by the specified virtual server."
	::= { ltmVirtualServRuleEntry 3 }

--==================================================================
-- Virtual_server_vlan
--==================================================================
ltmVirtualServVlanNumber OBJECT-TYPE
	SYNTAX INTEGER
	MAX-ACCESS read-only
	STATUS current
	DESCRIPTION
		"The number of ltmVirtualServVlan entries in the table."
	::= { ltmVirtualServVlan 1 }

ltmVirtualServVlanTable OBJECT-TYPE
	SYNTAX SEQUENCE OF LtmVirtualServVlanEntry
	MAX-ACCESS not-accessible
	STATUS current
	DESCRIPTION
		"A table containing VLAN information associated with virtual server."
	::= { ltmVirtualServVlan 2 }

ltmVirtualServVlanEntry OBJECT-TYPE
	SYNTAX  LtmVirtualServVlanEntry
	MAX-ACCESS not-accessible
	STATUS current
	DESCRIPTION
		"Columns in the ltmVirtualServVlan Table"
	INDEX {
		ltmVirtualServVlanVsName,
		ltmVirtualServVlanVlanName
	}
	::= { ltmVirtualServVlanTable 1 }

LtmVirtualServVlanEntry ::=
	SEQUENCE {
        	ltmVirtualServVlanVsName                                  LongDisplayString,
        	ltmVirtualServVlanVlanName                                LongDisplayString
	}

ltmVirtualServVlanVsName OBJECT-TYPE
	SYNTAX LongDisplayString
	MAX-ACCESS read-only
	STATUS current
	DESCRIPTION
		"The name of a virtual server."
	::= { ltmVirtualServVlanEntry 1 }

ltmVirtualServVlanVlanName OBJECT-TYPE
	SYNTAX LongDisplayString
	MAX-ACCESS read-only
	STATUS current
	DESCRIPTION
		"The name of a VLAN which the specified virtual server associated with."
	::= { ltmVirtualServVlanEntry 2 }

--==================================================================
-- Virtual_address
--==================================================================
ltmVirtualAddrNumber OBJECT-TYPE
	SYNTAX INTEGER
	MAX-ACCESS read-only
	STATUS current
	DESCRIPTION
		"The number of ltmVirtualAddr entries in the table."
	::= { ltmVirtualAddr 1 }

ltmVirtualAddrTable OBJECT-TYPE
	SYNTAX SEQUENCE OF LtmVirtualAddrEntry
	MAX-ACCESS not-accessible
	STATUS current
	DESCRIPTION
		"A table containing information of virtual server addresses."
	::= { ltmVirtualAddr 2 }

ltmVirtualAddrEntry OBJECT-TYPE
	SYNTAX  LtmVirtualAddrEntry
	MAX-ACCESS not-accessible
	STATUS current
	DESCRIPTION
		"Columns in the ltmVirtualAddr Table"
	INDEX {
		ltmVirtualAddrName
	}
	::= { ltmVirtualAddrTable 1 }

LtmVirtualAddrEntry ::=
	SEQUENCE {
        	ltmVirtualAddrAddrType                                    InetAddressType,
        	ltmVirtualAddrAddr                                        InetAddress,
        	ltmVirtualAddrEnabled                                     INTEGER,
        	ltmVirtualAddrConnLimit                                   Gauge,
        	ltmVirtualAddrArpEnabled                                  INTEGER,
        	ltmVirtualAddrSfFlags                                     INTEGER,
        	ltmVirtualAddrUnitId                                      Gauge,
        	ltmVirtualAddrRouteAdvertisement                          INTEGER,
        	ltmVirtualAddrAvailabilityState                           INTEGER,
        	ltmVirtualAddrEnabledState                                INTEGER,
        	ltmVirtualAddrDisabledParentType                          Gauge,
        	ltmVirtualAddrStatusReason                                LongDisplayString,
        	ltmVirtualAddrServer                                      INTEGER,
        	ltmVirtualAddrIsFloat                                     INTEGER,
        	ltmVirtualAddrName                                        LongDisplayString,
        	ltmVirtualAddrIcmpEcho                                    INTEGER
	}

ltmVirtualAddrAddrType OBJECT-TYPE
	SYNTAX InetAddressType
	MAX-ACCESS read-only
	STATUS current
	DESCRIPTION
		"The IP address type of ltmVirtualAddrAddr"
	::= { ltmVirtualAddrEntry 1 }

ltmVirtualAddrAddr OBJECT-TYPE
	SYNTAX InetAddress
	MAX-ACCESS read-only
	STATUS current
	DESCRIPTION
		"The IP address of a virtual address.
		It is interpreted within the context of an ltmVitualAddrAddrType value."
	::= { ltmVirtualAddrEntry 2 }

ltmVirtualAddrEnabled OBJECT-TYPE
	SYNTAX INTEGER {
		false(0),
		true(1)
	}
	MAX-ACCESS read-write
	STATUS current
	DESCRIPTION
		"The state indicating whether the specified virtual address is enabled or not."
	::= { ltmVirtualAddrEntry 3 }

ltmVirtualAddrConnLimit OBJECT-TYPE
	SYNTAX Gauge
	MAX-ACCESS read-only
	STATUS current
	DESCRIPTION
		"The maximum number of connections the specified virtual address is
		 allowed to have open at one time."
	::= { ltmVirtualAddrEntry 4 }

ltmVirtualAddrArpEnabled OBJECT-TYPE
	SYNTAX INTEGER {
		false(0),
		true(1)
	}
	MAX-ACCESS read-only
	STATUS current
	DESCRIPTION
		"The state indicating whether ARP for the specified virtual address
		is enabled or not."
	::= { ltmVirtualAddrEntry 5 }

ltmVirtualAddrSfFlags OBJECT-TYPE
	SYNTAX INTEGER {
		disabled(0),
		enabled(1)
	}
	MAX-ACCESS read-only
	STATUS	 deprecated
	DESCRIPTION
		"Deprecated! This feature has been eliminated.
		The flag to indicate whether connection mirroring is
		enabled for the specified virtual address."
	::= { ltmVirtualAddrEntry 6 }

ltmVirtualAddrUnitId OBJECT-TYPE
	SYNTAX Gauge
	MAX-ACCESS read-only
	STATUS current
	DESCRIPTION
		"The unit number associated with the specified virtual address."
	::= { ltmVirtualAddrEntry 7 }

ltmVirtualAddrRouteAdvertisement OBJECT-TYPE
	SYNTAX INTEGER {
		false(0),
		true(1),
		selective(2),
		always(3),
		any(4),
		all(5)
	}
	MAX-ACCESS read-only
	STATUS current
	DESCRIPTION
		"The state to determine if the specified virtual address should be
			readvertised by the ZebOS routing daemons or not.
		true/selective: route is advertised when virtual-address is available.
		always: route-advertisement is enabled regradless of the availability status.
		any: route is advertised when any of the contributing virtual server is available.
		all: route is advertised when all of the contributing virtual server is available."
	::= { ltmVirtualAddrEntry 8 }

ltmVirtualAddrAvailabilityState OBJECT-TYPE
	SYNTAX INTEGER {
		none(0),
		green(1),
		yellow(2),
		red(3),
		blue(4)
	}
	MAX-ACCESS read-only
	STATUS	 deprecated
	DESCRIPTION
		"Deprecated!
		Replaced by ltmVsAddrStatusAvailState under ltmVirtualAddrStatus.
		The state of the specified virtual address availability indicated in color."
	::= { ltmVirtualAddrEntry 9 }

ltmVirtualAddrEnabledState OBJECT-TYPE
	SYNTAX INTEGER {
		none(0),
		enabled(1),
		disabled(2),
		disabledbyparent(3)
	}
	MAX-ACCESS read-only
	STATUS	 deprecated
	DESCRIPTION
		"Deprecated!
		Replaced by ltmVsAddrStatusEnabledState under ltmVirtualAddrStatus.
		The state of the specified virtual address activity status,
		as specified by the user."
	::= { ltmVirtualAddrEntry 10 }

ltmVirtualAddrDisabledParentType OBJECT-TYPE
	SYNTAX Gauge
	MAX-ACCESS read-only
	STATUS	 deprecated
	DESCRIPTION
		"Deprecated!
		Replaced by ltmVsAddrStatusParentType under ltmVirtualAddrStatus.
		The type of parent object which disabled the specified virtual address."
	::= { ltmVirtualAddrEntry 11 }

ltmVirtualAddrStatusReason OBJECT-TYPE
	SYNTAX LongDisplayString
	MAX-ACCESS read-only
	STATUS	 deprecated
	DESCRIPTION
		"Deprecated!
		Replaced by ltmVsAddrStatusDetailReason under ltmVirtualAddrStatus.
		The detail description of the virtual address's status of parent object
		which disabled the specified virtual address."
	::= { ltmVirtualAddrEntry 12 }

ltmVirtualAddrServer OBJECT-TYPE
	SYNTAX INTEGER {
		none(0),
		any(1),
		all(2)
	}
	MAX-ACCESS read-only
	STATUS current
	DESCRIPTION
		"That state to control how status of virtual address is depending on
		status of virtual server.
		none: virtual address is always green regardless of virtual server status.
		any: any virtual server is green, virtual address is green.
		all: all virtual servers must be green before virtual address is declared as green."
	::= { ltmVirtualAddrEntry 13 }

ltmVirtualAddrIsFloat OBJECT-TYPE
	SYNTAX INTEGER {
		false(0),
		true(1)
	}
	MAX-ACCESS read-only
	STATUS current
	DESCRIPTION
		"The state indicating whether the virtual address should be shared
		between the redundant pair. This is typically used in one-armed
		Combo pair, where GTM is only licensed on one of the boxes."
	::= { ltmVirtualAddrEntry 14 }

ltmVirtualAddrName OBJECT-TYPE
	SYNTAX LongDisplayString
	MAX-ACCESS read-only
	STATUS current
	DESCRIPTION
		"Virtual Address name"
	::= { ltmVirtualAddrEntry 15 }

ltmVirtualAddrIcmpEcho OBJECT-TYPE
	SYNTAX INTEGER {
		disabled(0),
		always(1),
		selective(2),
		any(3),
		all(4)
	}
	MAX-ACCESS read-only
	STATUS current
	DESCRIPTION
		"The state determine whether the specified virtual address should reply to ICMP echo requests.
		always: ICMP echo reply will be sent in response to ICMP echo requests.
		selective: ICMP echo reply will sent be in response to ICMP echo requests, when availability status is true.
		any: ICMP echo reply will be sent in response to ICMP echo requests, when any of the contributing virtual server is available.
		all: ICMP echo reply will be sent in response to ICMP echo requests when all of the contributing virtual server is available."
	::= { ltmVirtualAddrEntry 16 }

--==================================================================
-- Virtual_address_stat
--==================================================================
ltmVirtualAddrStatResetStats OBJECT-TYPE
	SYNTAX INTEGER
	MAX-ACCESS read-write
	STATUS current
	DESCRIPTION
		"The action to reset resettable statistics data in ltmVirtualAddrStat.
		 Setting this value to 1 will reset statistics data.
		 Note, some statistics data may not be reset including data that are incremental counters."
	::= { ltmVirtualAddrStat 1 }

ltmVirtualAddrStatNumber OBJECT-TYPE
	SYNTAX INTEGER
	MAX-ACCESS read-only
	STATUS current
	DESCRIPTION
		"The number of ltmVirtualAddrStat entries in the table."
	::= { ltmVirtualAddrStat 2 }

ltmVirtualAddrStatTable OBJECT-TYPE
	SYNTAX SEQUENCE OF LtmVirtualAddrStatEntry
	MAX-ACCESS not-accessible
	STATUS current
	DESCRIPTION
		"A table containing statistic information of virtual server addresses."
	::= { ltmVirtualAddrStat 3 }

ltmVirtualAddrStatEntry OBJECT-TYPE
	SYNTAX  LtmVirtualAddrStatEntry
	MAX-ACCESS not-accessible
	STATUS current
	DESCRIPTION
		"Columns in the ltmVirtualAddrStat Table"
	INDEX {
		ltmVirtualAddrStatName
	}
	::= { ltmVirtualAddrStatTable 1 }

LtmVirtualAddrStatEntry ::=
	SEQUENCE {
        	ltmVirtualAddrStatAddrType                                InetAddressType,
        	ltmVirtualAddrStatAddr                                    InetAddress,
        	ltmVirtualAddrStatClientPktsIn                            Counter64,
        	ltmVirtualAddrStatClientBytesIn                           Counter64,
        	ltmVirtualAddrStatClientPktsOut                           Counter64,
        	ltmVirtualAddrStatClientBytesOut                          Counter64,
        	ltmVirtualAddrStatClientMaxConns                          Counter64,
        	ltmVirtualAddrStatClientTotConns                          Counter64,
        	ltmVirtualAddrStatClientCurConns                          Gauge,
        	ltmVirtualAddrStatPvaPktsIn                               Counter64,
        	ltmVirtualAddrStatPvaBytesIn                              Counter64,
        	ltmVirtualAddrStatPvaPktsOut                              Counter64,
        	ltmVirtualAddrStatPvaBytesOut                             Counter64,
        	ltmVirtualAddrStatPvaMaxConns                             Counter64,
        	ltmVirtualAddrStatPvaTotConns                             Counter64,
        	ltmVirtualAddrStatPvaCurConns                             Gauge,
        	ltmVirtualAddrStatTotPvaAssistConn                        Counter64,
        	ltmVirtualAddrStatCurrPvaAssistConn                       Gauge,
        	ltmVirtualAddrStatName                                    LongDisplayString
	}

ltmVirtualAddrStatAddrType OBJECT-TYPE
	SYNTAX InetAddressType
	MAX-ACCESS read-only
	STATUS	 deprecated
	DESCRIPTION
		"Deprecated! use name instead,
		The IP address type of ltmVirtualAddrStatAddr"
	::= { ltmVirtualAddrStatEntry 1 }

ltmVirtualAddrStatAddr OBJECT-TYPE
	SYNTAX InetAddress
	MAX-ACCESS read-only
	STATUS	 deprecated
	DESCRIPTION
		"Deprecated! use name instead,
	     The IP address of a virtual address. It is interpreted
		 within the context of a ltmVitualAddrStatAddrType value."
	::= { ltmVirtualAddrStatEntry 2 }

ltmVirtualAddrStatClientPktsIn OBJECT-TYPE
	SYNTAX Counter64
	MAX-ACCESS read-only
	STATUS current
	DESCRIPTION
		"The number of packets received by the specified virtual address
		from client-side."
	::= { ltmVirtualAddrStatEntry 3 }

ltmVirtualAddrStatClientBytesIn OBJECT-TYPE
	SYNTAX Counter64
	MAX-ACCESS read-only
	STATUS current
	DESCRIPTION
		"The number of bytes received by the specified virtual address
		from client-side."
	::= { ltmVirtualAddrStatEntry 4 }

ltmVirtualAddrStatClientPktsOut OBJECT-TYPE
	SYNTAX Counter64
	MAX-ACCESS read-only
	STATUS current
	DESCRIPTION
		"The number of packets sent to client-side from the specified virtual address."
	::= { ltmVirtualAddrStatEntry 5 }

ltmVirtualAddrStatClientBytesOut OBJECT-TYPE
	SYNTAX Counter64
	MAX-ACCESS read-only
	STATUS current
	DESCRIPTION
		"The number of bytes sent to client-side from the specified virtual address."
	::= { ltmVirtualAddrStatEntry 6 }

ltmVirtualAddrStatClientMaxConns OBJECT-TYPE
	SYNTAX Counter64
	MAX-ACCESS read-only
	STATUS current
	DESCRIPTION
		"The maximum connections to the specified virtual address from client-side."
	::= { ltmVirtualAddrStatEntry 7 }

ltmVirtualAddrStatClientTotConns OBJECT-TYPE
	SYNTAX Counter64
	MAX-ACCESS read-only
	STATUS current
	DESCRIPTION
		"The total connections to the specified virtual address from client-side."
	::= { ltmVirtualAddrStatEntry 8 }

ltmVirtualAddrStatClientCurConns OBJECT-TYPE
	SYNTAX Gauge
	MAX-ACCESS read-only
	STATUS current
	DESCRIPTION
		"The current connections to the specified virtual address from client-side."
	::= { ltmVirtualAddrStatEntry 9 }

ltmVirtualAddrStatPvaPktsIn OBJECT-TYPE
	SYNTAX Counter64
	MAX-ACCESS read-only
	STATUS current
	DESCRIPTION
		"The number of hardware accelerated packets received by the specified virtual address."
	::= { ltmVirtualAddrStatEntry 10 }

ltmVirtualAddrStatPvaBytesIn OBJECT-TYPE
	SYNTAX Counter64
	MAX-ACCESS read-only
	STATUS current
	DESCRIPTION
		"The number of hardware accelerated bytes received by the specified virtual address."
	::= { ltmVirtualAddrStatEntry 11 }

ltmVirtualAddrStatPvaPktsOut OBJECT-TYPE
	SYNTAX Counter64
	MAX-ACCESS read-only
	STATUS current
	DESCRIPTION
		"The number of hardware accelerated packets sent out from  the specified virtual address."
	::= { ltmVirtualAddrStatEntry 12 }

ltmVirtualAddrStatPvaBytesOut OBJECT-TYPE
	SYNTAX Counter64
	MAX-ACCESS read-only
	STATUS current
	DESCRIPTION
		"The number of hardware accelerated bytes sent out from the specified virtual address."
	::= { ltmVirtualAddrStatEntry 13 }

ltmVirtualAddrStatPvaMaxConns OBJECT-TYPE
	SYNTAX Counter64
	MAX-ACCESS read-only
	STATUS current
	DESCRIPTION
		"The maximum hardware accelerated connections to the specified virtual address."
	::= { ltmVirtualAddrStatEntry 14 }

ltmVirtualAddrStatPvaTotConns OBJECT-TYPE
	SYNTAX Counter64
	MAX-ACCESS read-only
	STATUS current
	DESCRIPTION
		"The total hardware accelerated connections to the specified virtual address."
	::= { ltmVirtualAddrStatEntry 15 }

ltmVirtualAddrStatPvaCurConns OBJECT-TYPE
	SYNTAX Gauge
	MAX-ACCESS read-only
	STATUS current
	DESCRIPTION
		"The current hardware accelerated connections to the specified virtual address."
	::= { ltmVirtualAddrStatEntry 16 }

ltmVirtualAddrStatTotPvaAssistConn OBJECT-TYPE
	SYNTAX Counter64
	MAX-ACCESS read-only
	STATUS current
	DESCRIPTION
		"The total number of connections to the specified virtual address,
		which are partially hardware accelerated."
	::= { ltmVirtualAddrStatEntry 17 }

ltmVirtualAddrStatCurrPvaAssistConn OBJECT-TYPE
	SYNTAX Gauge
	MAX-ACCESS read-only
	STATUS current
	DESCRIPTION
		"The current number of connections to the specified virtual address,
		which are partially hardware accelerated."
	::= { ltmVirtualAddrStatEntry 18 }

ltmVirtualAddrStatName OBJECT-TYPE
	SYNTAX LongDisplayString
	MAX-ACCESS read-only
	STATUS current
	DESCRIPTION
		"Virtual Address name"
	::= { ltmVirtualAddrStatEntry 19 }

--==================================================================
-- Profile_fasthttp
--==================================================================
ltmFastHttpProfileNumber OBJECT-TYPE
	SYNTAX INTEGER
	MAX-ACCESS read-only
	STATUS current
	DESCRIPTION
		"The number of ltmFastHttpProfile entries in the table."
	::= { ltmFastHttpProfile 1 }

ltmFastHttpProfileTable OBJECT-TYPE
	SYNTAX SEQUENCE OF LtmFastHttpProfileEntry
	MAX-ACCESS not-accessible
	STATUS current
	DESCRIPTION
		"A table containing information of Fast HTTP profile."
	::= { ltmFastHttpProfile 2 }

ltmFastHttpProfileEntry OBJECT-TYPE
	SYNTAX  LtmFastHttpProfileEntry
	MAX-ACCESS not-accessible
	STATUS current
	DESCRIPTION
		"Columns in the ltmFastHttpProfile Table"
	INDEX {
		ltmFastHttpProfileName
	}
	::= { ltmFastHttpProfileTable 1 }

LtmFastHttpProfileEntry ::=
	SEQUENCE {
        	ltmFastHttpProfileName                                    LongDisplayString,
        	ltmFastHttpProfileConfigSource                            INTEGER,
        	ltmFastHttpProfileDefaultName                             LongDisplayString,
        	ltmFastHttpProfileResetOnTimeout                          INTEGER,
        	ltmFastHttpProfileIdleTimeout                             Gauge,
        	ltmFastHttpProfileMssOverride                             Gauge,
        	ltmFastHttpProfileClientCloseTimeout                      Gauge,
        	ltmFastHttpProfileServerCloseTimeout                      Gauge,
        	ltmFastHttpProfileConnpoolMaxSize                         Gauge,
        	ltmFastHttpProfileConnpoolMinSize                         Gauge,
        	ltmFastHttpProfileConnpoolStep                            Gauge,
        	ltmFastHttpProfileConnpoolMaxReuse                        Gauge,
        	ltmFastHttpProfileConnpoolIdleTimeout                     Gauge,
        	ltmFastHttpProfileMaxHeaderSize                           Gauge,
        	ltmFastHttpProfileMaxRequests                             Gauge,
        	ltmFastHttpProfileInsertXforwardedFor                     INTEGER,
        	ltmFastHttpProfileHttp11CloseWorkarounds                  INTEGER,
        	ltmFastHttpProfileHeaderInsert                            LongDisplayString,
        	ltmFastHttpProfileUncleanShutdown                         INTEGER,
        	ltmFastHttpProfileForceHttp10Response                     INTEGER,
        	ltmFastHttpProfileLayer7                                  INTEGER,
        	ltmFastHttpProfileConnpoolReplenish                       INTEGER
	}

ltmFastHttpProfileName OBJECT-TYPE
	SYNTAX LongDisplayString
	MAX-ACCESS read-only
	STATUS current
	DESCRIPTION
		"The name of a fast HTTP profile."
	::= { ltmFastHttpProfileEntry 1 }

ltmFastHttpProfileConfigSource OBJECT-TYPE
	SYNTAX INTEGER {
		usercfg(0),
		basecfg(1)
	}
	MAX-ACCESS read-only
	STATUS current
	DESCRIPTION
		"The state that specifies whether this is a base/pre-configured profile
		or user defined profile."
	::= { ltmFastHttpProfileEntry 2 }

ltmFastHttpProfileDefaultName OBJECT-TYPE
	SYNTAX LongDisplayString
	MAX-ACCESS read-only
	STATUS current
	DESCRIPTION
		"The name of the profile from which the specified profile derives
		its attribute default values."
	::= { ltmFastHttpProfileEntry 3 }

ltmFastHttpProfileResetOnTimeout OBJECT-TYPE
	SYNTAX INTEGER {
		false(0),
		true(1)
	}
	MAX-ACCESS read-only
	STATUS current
	DESCRIPTION
		"If true and a TCP connection exceeds its idle_timeout,
		send a reset in addition to deleting the connection."
	::= { ltmFastHttpProfileEntry 4 }

ltmFastHttpProfileIdleTimeout OBJECT-TYPE
	SYNTAX Gauge
	MAX-ACCESS read-only
	STATUS current
	DESCRIPTION
		"Number of seconds without traffic before a connection
		is eligible for deletion."
	::= { ltmFastHttpProfileEntry 5 }

ltmFastHttpProfileMssOverride OBJECT-TYPE
	SYNTAX Gauge
	MAX-ACCESS read-only
	STATUS current
	DESCRIPTION
		"If non-zero and less than the 1460 default, this value
		overrides the maximum segment size for server-side flows."
	::= { ltmFastHttpProfileEntry 6 }

ltmFastHttpProfileClientCloseTimeout OBJECT-TYPE
	SYNTAX Gauge
	MAX-ACCESS read-only
	STATUS current
	DESCRIPTION
		"Idle timeout override when waiting for the client to close.
		This occurs after a client FIN is received or after a FIN
		is sent. 0 is immediate, -1 is indefinite."
	::= { ltmFastHttpProfileEntry 7 }

ltmFastHttpProfileServerCloseTimeout OBJECT-TYPE
	SYNTAX Gauge
	MAX-ACCESS read-only
	STATUS current
	DESCRIPTION
		"Idle timeout override when waiting for the server to close.
		This occurs if the server flow is not suitable for reuse or
		after a FIN is received on an unspliced server connection.
		0 is immediate, -1 is indefinite."
	::= { ltmFastHttpProfileEntry 8 }

ltmFastHttpProfileConnpoolMaxSize OBJECT-TYPE
	SYNTAX Gauge
	MAX-ACCESS read-only
	STATUS current
	DESCRIPTION
		"Maximum number of connections to any given LB pool.
		0 for unlimited."
	::= { ltmFastHttpProfileEntry 9 }

ltmFastHttpProfileConnpoolMinSize OBJECT-TYPE
	SYNTAX Gauge
	MAX-ACCESS read-only
	STATUS current
	DESCRIPTION
		"Minimum number of connections to any given LB pool.
		0 is an acceptable value."
	::= { ltmFastHttpProfileEntry 10 }

ltmFastHttpProfileConnpoolStep OBJECT-TYPE
	SYNTAX Gauge
	MAX-ACCESS read-only
	STATUS current
	DESCRIPTION
		"Connection ramp-up increment. Must be greater than 0."
	::= { ltmFastHttpProfileEntry 11 }

ltmFastHttpProfileConnpoolMaxReuse OBJECT-TYPE
	SYNTAX Gauge
	MAX-ACCESS read-only
	STATUS current
	DESCRIPTION
		"Maximum number of times a server-side flow will be reused.
		0 for unlimited."
	::= { ltmFastHttpProfileEntry 12 }

ltmFastHttpProfileConnpoolIdleTimeout OBJECT-TYPE
	SYNTAX Gauge
	MAX-ACCESS read-only
	STATUS current
	DESCRIPTION
		"Idle timeout override for unspliced server-side flows in the
		reuse pool. 0 is disabled, i.e. use the default idle timeout."
	::= { ltmFastHttpProfileEntry 13 }

ltmFastHttpProfileMaxHeaderSize OBJECT-TYPE
	SYNTAX Gauge
	MAX-ACCESS read-only
	STATUS current
	DESCRIPTION
		"Maximum amount of data that will be buffered in order to
		make a content-switching decision."
	::= { ltmFastHttpProfileEntry 14 }

ltmFastHttpProfileMaxRequests OBJECT-TYPE
	SYNTAX Gauge
	MAX-ACCESS read-only
	STATUS current
	DESCRIPTION
		"Maximum number of requests on a client-side flow before
		the flow is shutdown. 0 for unlimited."
	::= { ltmFastHttpProfileEntry 15 }

ltmFastHttpProfileInsertXforwardedFor OBJECT-TYPE
	SYNTAX INTEGER {
		disabled(0),
		enabled(1)
	}
	MAX-ACCESS read-only
	STATUS current
	DESCRIPTION
		"The state whether to insert or replace X-Forwarded-For header
		with client IP."
	::= { ltmFastHttpProfileEntry 16 }

ltmFastHttpProfileHttp11CloseWorkarounds OBJECT-TYPE
	SYNTAX INTEGER {
		false(0),
		true(1)
	}
	MAX-ACCESS read-only
	STATUS current
	DESCRIPTION
		"The state to workaround problems with certain brands of benchmarking
		software that cannot handle FIN-PUSH on HTTP/1.1 responses."
	::= { ltmFastHttpProfileEntry 17 }

ltmFastHttpProfileHeaderInsert OBJECT-TYPE
	SYNTAX LongDisplayString
	MAX-ACCESS read-only
	STATUS current
	DESCRIPTION
		"Insert the given string as a header. If the header already
		exists, it is not replaced. Unlike HTTP, this string does not
		support rule command expansion."
	::= { ltmFastHttpProfileEntry 18 }

ltmFastHttpProfileUncleanShutdown OBJECT-TYPE
	SYNTAX INTEGER {
		disable(0),
		enable(1),
		fast(2)
	}
	MAX-ACCESS read-only
	STATUS current
	DESCRIPTION
		"The mode to indicate whether to do unclean shutdown for client connections."
	::= { ltmFastHttpProfileEntry 19 }

ltmFastHttpProfileForceHttp10Response OBJECT-TYPE
	SYNTAX INTEGER {
		false(0),
		true(1)
	}
	MAX-ACCESS read-only
	STATUS current
	DESCRIPTION
		"The state to indicate whether to rewrite server's HTTP version to 1.0 in status
		line in order to dissuade the client from pipelining or chunking."
	::= { ltmFastHttpProfileEntry 20 }

ltmFastHttpProfileLayer7 OBJECT-TYPE
	SYNTAX INTEGER {
		false(0),
		true(1)
	}
	MAX-ACCESS read-only
	STATUS current
	DESCRIPTION
		"The state that if false, we don't parse HTTP requests. This is useful for
		providing SYN-proxy protection for L4 connections through a SNAT where the
		client sends data to the server before the server responds."
	::= { ltmFastHttpProfileEntry 21 }

ltmFastHttpProfileConnpoolReplenish OBJECT-TYPE
	SYNTAX INTEGER {
		false(0),
		true(1)
	}
	MAX-ACCESS read-only
	STATUS current
	DESCRIPTION
		"The state that specifies whether the connpool should be replenished
		to its prior number of connections when a connection is closed
		by the server. If this is disabled, then we  will only replenish
		a closed server side connection residing in the connpool if there are
		less than ltmFastHttpProfileMinSize (see above) connections
		in the pool."
	::= { ltmFastHttpProfileEntry 22 }

--==================================================================
-- Profile_fasthttp_stat
--==================================================================
ltmFastHttpProfileStatResetStats OBJECT-TYPE
	SYNTAX INTEGER
	MAX-ACCESS read-write
	STATUS current
	DESCRIPTION
		"The action to reset resettable statistics data in ltmFastHttpProfileStat.
		 Setting this value to 1 will reset statistics data.
		 Note, some statistics data may not be reset including data that are incremental counters."
	::= { ltmFastHttpProfileStat 1 }

ltmFastHttpProfileStatNumber OBJECT-TYPE
	SYNTAX INTEGER
	MAX-ACCESS read-only
	STATUS current
	DESCRIPTION
		"The number of ltmFastHttpProfileStat entries in the table."
	::= { ltmFastHttpProfileStat 2 }

ltmFastHttpProfileStatTable OBJECT-TYPE
	SYNTAX SEQUENCE OF LtmFastHttpProfileStatEntry
	MAX-ACCESS not-accessible
	STATUS current
	DESCRIPTION
		"A table containing statistic information of Fast HTTP profile."
	::= { ltmFastHttpProfileStat 3 }

ltmFastHttpProfileStatEntry OBJECT-TYPE
	SYNTAX  LtmFastHttpProfileStatEntry
	MAX-ACCESS not-accessible
	STATUS current
	DESCRIPTION
		"Columns in the ltmFastHttpProfileStat Table"
	INDEX {
		ltmFastHttpProfileStatName
	}
	::= { ltmFastHttpProfileStatTable 1 }

LtmFastHttpProfileStatEntry ::=
	SEQUENCE {
        	ltmFastHttpProfileStatName                                LongDisplayString,
        	ltmFastHttpProfileStatClientSyns                          Counter64,
        	ltmFastHttpProfileStatClientAccepts                       Counter64,
        	ltmFastHttpProfileStatServerConnects                      Counter64,
        	ltmFastHttpProfileStatConnpoolCurSize                     Gauge,
        	ltmFastHttpProfileStatConnpoolMaxSize                     Gauge,
        	ltmFastHttpProfileStatConnpoolReuses                      Counter64,
        	ltmFastHttpProfileStatConnpoolExhausted                   Counter64,
        	ltmFastHttpProfileStatNumberReqs                          Counter64,
        	ltmFastHttpProfileStatUnbufferedReqs                      Counter64,
        	ltmFastHttpProfileStatGetReqs                             Counter64,
        	ltmFastHttpProfileStatPostReqs                            Counter64,
        	ltmFastHttpProfileStatV9Reqs                              Counter64,
        	ltmFastHttpProfileStatV10Reqs                             Counter64,
        	ltmFastHttpProfileStatV11Reqs                             Counter64,
        	ltmFastHttpProfileStatResp2xxCnt                          Counter64,
        	ltmFastHttpProfileStatResp3xxCnt                          Counter64,
        	ltmFastHttpProfileStatResp4xxCnt                          Counter64,
        	ltmFastHttpProfileStatResp5xxCnt                          Counter64,
        	ltmFastHttpProfileStatReqParseErrors                      Counter64,
        	ltmFastHttpProfileStatRespParseErrors                     Counter64,
        	ltmFastHttpProfileStatClientRxBad                         Counter64,
        	ltmFastHttpProfileStatServerRxBad                         Counter64,
        	ltmFastHttpProfileStatPipelinedReqs                       Counter64
	}

ltmFastHttpProfileStatName OBJECT-TYPE
	SYNTAX LongDisplayString
	MAX-ACCESS read-only
	STATUS current
	DESCRIPTION
		"The name of a fast HTTP profile."
	::= { ltmFastHttpProfileStatEntry 1 }

ltmFastHttpProfileStatClientSyns OBJECT-TYPE
	SYNTAX Counter64
	MAX-ACCESS read-only
	STATUS current
	DESCRIPTION
		"The total number of client SYN cookies generated."
	::= { ltmFastHttpProfileStatEntry 2 }

ltmFastHttpProfileStatClientAccepts OBJECT-TYPE
	SYNTAX Counter64
	MAX-ACCESS read-only
	STATUS current
	DESCRIPTION
		"The total number of client TCP accepts."
	::= { ltmFastHttpProfileStatEntry 3 }

ltmFastHttpProfileStatServerConnects OBJECT-TYPE
	SYNTAX Counter64
	MAX-ACCESS read-only
	STATUS current
	DESCRIPTION
		"The total number of server TCP connects."
	::= { ltmFastHttpProfileStatEntry 4 }

ltmFastHttpProfileStatConnpoolCurSize OBJECT-TYPE
	SYNTAX Gauge
	MAX-ACCESS read-only
	STATUS current
	DESCRIPTION
		"Number of available server-side flows in the reuse pool."
	::= { ltmFastHttpProfileStatEntry 5 }

ltmFastHttpProfileStatConnpoolMaxSize OBJECT-TYPE
	SYNTAX Gauge
	MAX-ACCESS read-only
	STATUS current
	DESCRIPTION
		"Max number of available server-side flows in the reuse pool."
	::= { ltmFastHttpProfileStatEntry 6 }

ltmFastHttpProfileStatConnpoolReuses OBJECT-TYPE
	SYNTAX Counter64
	MAX-ACCESS read-only
	STATUS current
	DESCRIPTION
		"Number of times a server-side flow was reused from the pool."
	::= { ltmFastHttpProfileStatEntry 7 }

ltmFastHttpProfileStatConnpoolExhausted OBJECT-TYPE
	SYNTAX Counter64
	MAX-ACCESS read-only
	STATUS current
	DESCRIPTION
		"Number of times the reuse pool was exhausted."
	::= { ltmFastHttpProfileStatEntry 8 }

ltmFastHttpProfileStatNumberReqs OBJECT-TYPE
	SYNTAX Counter64
	MAX-ACCESS read-only
	STATUS current
	DESCRIPTION
		"The total number of http requests."
	::= { ltmFastHttpProfileStatEntry 9 }

ltmFastHttpProfileStatUnbufferedReqs OBJECT-TYPE
	SYNTAX Counter64
	MAX-ACCESS read-only
	STATUS current
	DESCRIPTION
		"The total number of unbuffered requests."
	::= { ltmFastHttpProfileStatEntry 10 }

ltmFastHttpProfileStatGetReqs OBJECT-TYPE
	SYNTAX Counter64
	MAX-ACCESS read-only
	STATUS current
	DESCRIPTION
		"The total number of get requests."
	::= { ltmFastHttpProfileStatEntry 11 }

ltmFastHttpProfileStatPostReqs OBJECT-TYPE
	SYNTAX Counter64
	MAX-ACCESS read-only
	STATUS current
	DESCRIPTION
		"The total number of post requests."
	::= { ltmFastHttpProfileStatEntry 12 }

ltmFastHttpProfileStatV9Reqs OBJECT-TYPE
	SYNTAX Counter64
	MAX-ACCESS read-only
	STATUS current
	DESCRIPTION
		"The total number of version 9 requests."
	::= { ltmFastHttpProfileStatEntry 13 }

ltmFastHttpProfileStatV10Reqs OBJECT-TYPE
	SYNTAX Counter64
	MAX-ACCESS read-only
	STATUS current
	DESCRIPTION
		"The total number of version 10 requests."
	::= { ltmFastHttpProfileStatEntry 14 }

ltmFastHttpProfileStatV11Reqs OBJECT-TYPE
	SYNTAX Counter64
	MAX-ACCESS read-only
	STATUS current
	DESCRIPTION
		"The total number of version 11 requests."
	::= { ltmFastHttpProfileStatEntry 15 }

ltmFastHttpProfileStatResp2xxCnt OBJECT-TYPE
	SYNTAX Counter64
	MAX-ACCESS read-only
	STATUS current
	DESCRIPTION
		"Number of server-side responses in range of 200 to 206
		(successful responses)."
	::= { ltmFastHttpProfileStatEntry 16 }

ltmFastHttpProfileStatResp3xxCnt OBJECT-TYPE
	SYNTAX Counter64
	MAX-ACCESS read-only
	STATUS current
	DESCRIPTION
		"Number of server-side responses in range of 300 to 307
		(redirection responses)."
	::= { ltmFastHttpProfileStatEntry 17 }

ltmFastHttpProfileStatResp4xxCnt OBJECT-TYPE
	SYNTAX Counter64
	MAX-ACCESS read-only
	STATUS current
	DESCRIPTION
		"Number of server-side responses in range of 400 to 417 (client errors). "
	::= { ltmFastHttpProfileStatEntry 18 }

ltmFastHttpProfileStatResp5xxCnt OBJECT-TYPE
	SYNTAX Counter64
	MAX-ACCESS read-only
	STATUS current
	DESCRIPTION
		"Number of server-side responses in range of 500 to 505 (server errors)."
	::= { ltmFastHttpProfileStatEntry 19 }

ltmFastHttpProfileStatReqParseErrors OBJECT-TYPE
	SYNTAX Counter64
	MAX-ACCESS read-only
	STATUS current
	DESCRIPTION
		"Number of request parse errors."
	::= { ltmFastHttpProfileStatEntry 20 }

ltmFastHttpProfileStatRespParseErrors OBJECT-TYPE
	SYNTAX Counter64
	MAX-ACCESS read-only
	STATUS current
	DESCRIPTION
		"Number of response parse errors."
	::= { ltmFastHttpProfileStatEntry 21 }

ltmFastHttpProfileStatClientRxBad OBJECT-TYPE
	SYNTAX Counter64
	MAX-ACCESS read-only
	STATUS current
	DESCRIPTION
		"Number of bad TCP segments dropped from client-side."
	::= { ltmFastHttpProfileStatEntry 22 }

ltmFastHttpProfileStatServerRxBad OBJECT-TYPE
	SYNTAX Counter64
	MAX-ACCESS read-only
	STATUS current
	DESCRIPTION
		"Number of bad TCP segments dropped from server-side."
	::= { ltmFastHttpProfileStatEntry 23 }

ltmFastHttpProfileStatPipelinedReqs OBJECT-TYPE
	SYNTAX Counter64
	MAX-ACCESS read-only
	STATUS current
	DESCRIPTION
		"Number of pipelined HTTP requests detected."
	::= { ltmFastHttpProfileStatEntry 24 }

--==================================================================
-- Profile_xml
--==================================================================
ltmXmlProfileNumber OBJECT-TYPE
	SYNTAX INTEGER
	MAX-ACCESS read-only
	STATUS current
	DESCRIPTION
		"The number of ltmXmlProfile entries in the table."
	::= { ltmXmlProfile 1 }

ltmXmlProfileTable OBJECT-TYPE
	SYNTAX SEQUENCE OF LtmXmlProfileEntry
	MAX-ACCESS not-accessible
	STATUS current
	DESCRIPTION
		"A table containing information of XML profile."
	::= { ltmXmlProfile 2 }

ltmXmlProfileEntry OBJECT-TYPE
	SYNTAX  LtmXmlProfileEntry
	MAX-ACCESS not-accessible
	STATUS current
	DESCRIPTION
		"Columns in the ltmXmlProfile Table"
	INDEX {
		ltmXmlProfileName
	}
	::= { ltmXmlProfileTable 1 }

LtmXmlProfileEntry ::=
	SEQUENCE {
        	ltmXmlProfileName                                         LongDisplayString,
        	ltmXmlProfileConfigSource                                 INTEGER,
        	ltmXmlProfileDefaultName                                  LongDisplayString,
        	ltmXmlProfileAbortOnError                                 INTEGER,
        	ltmXmlProfileMaxBufferSize                                Gauge,
        	ltmXmlProfileMultipleQueryMatches                         INTEGER
	}

ltmXmlProfileName OBJECT-TYPE
	SYNTAX LongDisplayString
	MAX-ACCESS read-only
	STATUS current
	DESCRIPTION
		"The name of a XML profile."
	::= { ltmXmlProfileEntry 1 }

ltmXmlProfileConfigSource OBJECT-TYPE
	SYNTAX INTEGER {
		usercfg(0),
		basecfg(1)
	}
	MAX-ACCESS read-only
	STATUS current
	DESCRIPTION
		"The state that specifies whether this is a base/pre-configured profile
		or user defined profile."
	::= { ltmXmlProfileEntry 2 }

ltmXmlProfileDefaultName OBJECT-TYPE
	SYNTAX LongDisplayString
	MAX-ACCESS read-only
	STATUS current
	DESCRIPTION
		"The name of the profile from which the specified profile derives
		its attribute default values."
	::= { ltmXmlProfileEntry 3 }

ltmXmlProfileAbortOnError OBJECT-TYPE
	SYNTAX INTEGER {
		false(0),
		true(1)
	}
	MAX-ACCESS read-only
	STATUS	 deprecated
	DESCRIPTION
		"Deprecated! The state that if true, abort the connection on errors."
	::= { ltmXmlProfileEntry 4 }

ltmXmlProfileMaxBufferSize OBJECT-TYPE
	SYNTAX Gauge
	MAX-ACCESS read-only
	STATUS	 deprecated
	DESCRIPTION
		"Deprecated! The value that specifies the maximum buffer size for the specified profile."
	::= { ltmXmlProfileEntry 5 }

ltmXmlProfileMultipleQueryMatches OBJECT-TYPE
	SYNTAX INTEGER {
		false(0),
		true(1)
	}
	MAX-ACCESS read-only
	STATUS current
	DESCRIPTION
		"The state that if true, multiple matches for a single XPath query are enabled."
	::= { ltmXmlProfileEntry 6 }

--==================================================================
-- Profile_xml_stat
--==================================================================
ltmXmlProfileStatResetStats OBJECT-TYPE
	SYNTAX INTEGER
	MAX-ACCESS read-write
	STATUS current
	DESCRIPTION
		"The action to reset resettable statistics data in ltmXmlProfileStat.
		 Setting this value to 1 will reset statistics data.
		 Note, some statistics data may not be reset including data that are incremental counters."
	::= { ltmXmlProfileStat 1 }

ltmXmlProfileStatNumber OBJECT-TYPE
	SYNTAX INTEGER
	MAX-ACCESS read-only
	STATUS current
	DESCRIPTION
		"The number of ltmXmlProfileStat entries in the table."
	::= { ltmXmlProfileStat 2 }

ltmXmlProfileStatTable OBJECT-TYPE
	SYNTAX SEQUENCE OF LtmXmlProfileStatEntry
	MAX-ACCESS not-accessible
	STATUS current
	DESCRIPTION
		"A table containing statistic information of XML profile."
	::= { ltmXmlProfileStat 3 }

ltmXmlProfileStatEntry OBJECT-TYPE
	SYNTAX  LtmXmlProfileStatEntry
	MAX-ACCESS not-accessible
	STATUS current
	DESCRIPTION
		"Columns in the ltmXmlProfileStat Table"
	INDEX {
		ltmXmlProfileStatName
	}
	::= { ltmXmlProfileStatTable 1 }

LtmXmlProfileStatEntry ::=
	SEQUENCE {
        	ltmXmlProfileStatName                                     LongDisplayString,
        	ltmXmlProfileStatNumErrors                                Counter64,
        	ltmXmlProfileStatNumInspectedDocuments                    Counter64,
        	ltmXmlProfileStatNumDocumentsWithOneMatch                 Counter64,
        	ltmXmlProfileStatNumDocumentsWithTwoMatches               Counter64,
        	ltmXmlProfileStatNumDocumentsWithThreeMatches             Counter64,
        	ltmXmlProfileStatNumDocumentsWithNoMatches                Counter64,
        	ltmXmlProfileStatNumMalformedDocuments                    Counter64
	}

ltmXmlProfileStatName OBJECT-TYPE
	SYNTAX LongDisplayString
	MAX-ACCESS read-only
	STATUS current
	DESCRIPTION
		"The name of a XML profile."
	::= { ltmXmlProfileStatEntry 1 }

ltmXmlProfileStatNumErrors OBJECT-TYPE
	SYNTAX Counter64
	MAX-ACCESS read-only
	STATUS	 deprecated
	DESCRIPTION
		"Deprecated! The total number of XML parsing errors."
	::= { ltmXmlProfileStatEntry 2 }

ltmXmlProfileStatNumInspectedDocuments OBJECT-TYPE
	SYNTAX Counter64
	MAX-ACCESS read-only
	STATUS current
	DESCRIPTION
		"The total number of inspected XML documents."
	::= { ltmXmlProfileStatEntry 3 }

ltmXmlProfileStatNumDocumentsWithOneMatch OBJECT-TYPE
	SYNTAX Counter64
	MAX-ACCESS read-only
	STATUS current
	DESCRIPTION
		"The total number of XML documents in which one XPath query match was found."
	::= { ltmXmlProfileStatEntry 4 }

ltmXmlProfileStatNumDocumentsWithTwoMatches OBJECT-TYPE
	SYNTAX Counter64
	MAX-ACCESS read-only
	STATUS current
	DESCRIPTION
		"The total number of XML documents in which two XPath query matches were found."
	::= { ltmXmlProfileStatEntry 5 }

ltmXmlProfileStatNumDocumentsWithThreeMatches OBJECT-TYPE
	SYNTAX Counter64
	MAX-ACCESS read-only
	STATUS current
	DESCRIPTION
		"The total number of XML documents in which three XPath query matches were found."
	::= { ltmXmlProfileStatEntry 6 }

ltmXmlProfileStatNumDocumentsWithNoMatches OBJECT-TYPE
	SYNTAX Counter64
	MAX-ACCESS read-only
	STATUS current
	DESCRIPTION
		"The total number of XML documents in which no XPath query matches were found."
	::= { ltmXmlProfileStatEntry 7 }

ltmXmlProfileStatNumMalformedDocuments OBJECT-TYPE
	SYNTAX Counter64
	MAX-ACCESS read-only
	STATUS current
	DESCRIPTION
		"The total number of malformed XML documents."
	::= { ltmXmlProfileStatEntry 8 }

--==================================================================
-- Profile_http_ramcache_uri_excludes
--==================================================================
ltmRamUriExclNumber OBJECT-TYPE
	SYNTAX INTEGER
	MAX-ACCESS read-only
	STATUS	 deprecated
	DESCRIPTION
		"Deprecated!.
		The number of ltmHttpProfileRamUriExcl entries in the table."
	::= { ltmHttpProfileRamUriExcl 1 }

ltmRamUriExclTable OBJECT-TYPE
	SYNTAX SEQUENCE OF LtmRamUriExclEntry
	MAX-ACCESS not-accessible
	STATUS deprecated
	DESCRIPTION
		"A table containing information of RAM cached excludes URI's
		in HTTP profiles."
	::= { ltmHttpProfileRamUriExcl 2 }

ltmRamUriExclEntry OBJECT-TYPE
	SYNTAX  LtmRamUriExclEntry
	MAX-ACCESS not-accessible
	STATUS deprecated
	DESCRIPTION
		"Columns in the ltmRamUriExcl Table"
	INDEX {
		ltmRamUriExclName,
		ltmRamUriExclIndex
	}
	::= { ltmRamUriExclTable 1 }

LtmRamUriExclEntry ::=
	SEQUENCE {
        	ltmRamUriExclName                                         LongDisplayString,
        	ltmRamUriExclIndex                                        INTEGER,
        	ltmRamUriExclUri                                          LongDisplayString
	}

ltmRamUriExclName OBJECT-TYPE
	SYNTAX LongDisplayString
	MAX-ACCESS read-only
	STATUS	 deprecated
	DESCRIPTION
		"The name of a HTTP profile."
	::= { ltmRamUriExclEntry 1 }

ltmRamUriExclIndex OBJECT-TYPE
	SYNTAX INTEGER(0..2147483647)
	MAX-ACCESS read-only
	STATUS	 deprecated
	DESCRIPTION
		"The index of RAM cached excludes URI for the specified HTTP profile."
	::= { ltmRamUriExclEntry 2 }

ltmRamUriExclUri OBJECT-TYPE
	SYNTAX LongDisplayString
	MAX-ACCESS read-only
	STATUS	 deprecated
	DESCRIPTION
		"The RAM cached excludes URI for the specified profile."
	::= { ltmRamUriExclEntry 3 }

--==================================================================
-- Profile_http_ramcache_uri_includes
--==================================================================
ltmRamUriInclNumber OBJECT-TYPE
	SYNTAX INTEGER
	MAX-ACCESS read-only
	STATUS	 deprecated
	DESCRIPTION
		"Deprecated!.
		The number of ltmHttpProfileRamUriIncl entries in the table."
	::= { ltmHttpProfileRamUriIncl 1 }

ltmRamUriInclTable OBJECT-TYPE
	SYNTAX SEQUENCE OF LtmRamUriInclEntry
	MAX-ACCESS not-accessible
	STATUS deprecated
	DESCRIPTION
		"A table containing information of RAM cached includes URI's
		in HTTP profiles."
	::= { ltmHttpProfileRamUriIncl 2 }

ltmRamUriInclEntry OBJECT-TYPE
	SYNTAX  LtmRamUriInclEntry
	MAX-ACCESS not-accessible
	STATUS deprecated
	DESCRIPTION
		"Columns in the ltmRamUriIncl Table"
	INDEX {
		ltmRamUriInclName,
		ltmRamUriInclIndex
	}
	::= { ltmRamUriInclTable 1 }

LtmRamUriInclEntry ::=
	SEQUENCE {
        	ltmRamUriInclName                                         LongDisplayString,
        	ltmRamUriInclIndex                                        INTEGER,
        	ltmRamUriInclUri                                          LongDisplayString
	}

ltmRamUriInclName OBJECT-TYPE
	SYNTAX LongDisplayString
	MAX-ACCESS read-only
	STATUS	 deprecated
	DESCRIPTION
		"The name of a HTTP profile."
	::= { ltmRamUriInclEntry 1 }

ltmRamUriInclIndex OBJECT-TYPE
	SYNTAX INTEGER(0..2147483647)
	MAX-ACCESS read-only
	STATUS	 deprecated
	DESCRIPTION
		"The index of RAM cached includes URI for the specified HTTP profile."
	::= { ltmRamUriInclEntry 2 }

ltmRamUriInclUri OBJECT-TYPE
	SYNTAX LongDisplayString
	MAX-ACCESS read-only
	STATUS	 deprecated
	DESCRIPTION
		"The RAM cached includes URI for the specified profile."
	::= { ltmRamUriInclEntry 3 }

--==================================================================
-- Profile_http_ramcache_uri_pinned
--==================================================================
ltmRamUriPinNumber OBJECT-TYPE
	SYNTAX INTEGER
	MAX-ACCESS read-only
	STATUS	 deprecated
	DESCRIPTION
		"Deprecated!.
		The number of ltmHttpProfileRamUriPin entries in the table."
	::= { ltmHttpProfileRamUriPin 1 }

ltmRamUriPinTable OBJECT-TYPE
	SYNTAX SEQUENCE OF LtmRamUriPinEntry
	MAX-ACCESS not-accessible
	STATUS deprecated
	DESCRIPTION
		"A table containing information of RAM cached URI's pinned
		in HTTP profiles."
	::= { ltmHttpProfileRamUriPin 2 }

ltmRamUriPinEntry OBJECT-TYPE
	SYNTAX  LtmRamUriPinEntry
	MAX-ACCESS not-accessible
	STATUS deprecated
	DESCRIPTION
		"Columns in the ltmRamUriPin Table"
	INDEX {
		ltmRamUriPinName,
		ltmRamUriPinIndex
	}
	::= { ltmRamUriPinTable 1 }

LtmRamUriPinEntry ::=
	SEQUENCE {
        	ltmRamUriPinName                                          LongDisplayString,
        	ltmRamUriPinIndex                                         INTEGER,
        	ltmRamUriPinUri                                           LongDisplayString
	}

ltmRamUriPinName OBJECT-TYPE
	SYNTAX LongDisplayString
	MAX-ACCESS read-only
	STATUS	 deprecated
	DESCRIPTION
		"The name of a HTTP profile."
	::= { ltmRamUriPinEntry 1 }

ltmRamUriPinIndex OBJECT-TYPE
	SYNTAX INTEGER(0..2147483647)
	MAX-ACCESS read-only
	STATUS	 deprecated
	DESCRIPTION
		"The index of RAM cached URI pinned for the specified HTTP profile."
	::= { ltmRamUriPinEntry 2 }

ltmRamUriPinUri OBJECT-TYPE
	SYNTAX LongDisplayString
	MAX-ACCESS read-only
	STATUS	 deprecated
	DESCRIPTION
		"The RAM cached URI pinned for the specified profile."
	::= { ltmRamUriPinEntry 3 }

--==================================================================
-- Profile_dns
--==================================================================
ltmDnsProfileNumber OBJECT-TYPE
	SYNTAX INTEGER
	MAX-ACCESS read-only
	STATUS current
	DESCRIPTION
		"The number of ltmDnsProfile entries in the table."
	::= { ltmDnsProfile 1 }

ltmDnsProfileTable OBJECT-TYPE
	SYNTAX SEQUENCE OF LtmDnsProfileEntry
	MAX-ACCESS not-accessible
	STATUS current
	DESCRIPTION
		"A table containing information for DNS profiles."
	::= { ltmDnsProfile 2 }

ltmDnsProfileEntry OBJECT-TYPE
	SYNTAX  LtmDnsProfileEntry
	MAX-ACCESS not-accessible
	STATUS current
	DESCRIPTION
		"Columns in the ltmDnsProfile Table"
	INDEX {
		ltmDnsProfileName
	}
	::= { ltmDnsProfileTable 1 }

LtmDnsProfileEntry ::=
	SEQUENCE {
        	ltmDnsProfileName                                         LongDisplayString,
        	ltmDnsProfileConfigSource                                 INTEGER,
        	ltmDnsProfileDefaultName                                  LongDisplayString,
        	ltmDnsProfileGtmEnabled                                   INTEGER,
        	ltmDnsProfileDns64Mode                                    INTEGER,
        	ltmDnsProfileDns64PrefixType                              InetAddressType,
        	ltmDnsProfileDns64Prefix                                  InetAddress,
        	ltmDnsProfileDns64AdditionalRewrite                       INTEGER,
        	ltmDnsProfileDnsLastAction                                INTEGER,
        	ltmDnsProfileUseLocalBind                                 INTEGER,
        	ltmDnsProfileDnsExpressEnabled                            INTEGER,
        	ltmDnsProfileDnssecEnabled                                INTEGER,
        	ltmDnsProfileCacheEnabled                                 INTEGER,
        	ltmDnsProfileDnsCache                                     LongDisplayString,
        	ltmDnsProfileProcessRd                                    INTEGER,
        	ltmDnsProfileAvrDnsStatSampleRate                         Gauge,
        	ltmDnsProfileSecurity                                     LongDisplayString,
        	ltmDnsProfileSecurityEnabled                              INTEGER,
        	ltmDnsProfileLoggingProfile                               LongDisplayString,
        	ltmDnsProfileLoggingEnabled                               INTEGER,
        	ltmDnsProfileFastDnsEnabled                               INTEGER,
        	ltmDnsProfileHwValidation                                 INTEGER,
        	ltmDnsProfileHwCache                                      INTEGER
	}

ltmDnsProfileName OBJECT-TYPE
	SYNTAX LongDisplayString
	MAX-ACCESS read-only
	STATUS current
	DESCRIPTION
		"The name of a DNS profile."
	::= { ltmDnsProfileEntry 1 }

ltmDnsProfileConfigSource OBJECT-TYPE
	SYNTAX INTEGER {
		usercfg(0),
		basecfg(1)
	}
	MAX-ACCESS read-only
	STATUS current
	DESCRIPTION
		"The state that specifies whether this is a base/pre-configured profile
		or user defined profile."
	::= { ltmDnsProfileEntry 2 }

ltmDnsProfileDefaultName OBJECT-TYPE
	SYNTAX LongDisplayString
	MAX-ACCESS read-only
	STATUS current
	DESCRIPTION
		"The name of the profile from which the specified profile derives
		its attribute default values."
	::= { ltmDnsProfileEntry 3 }

ltmDnsProfileGtmEnabled OBJECT-TYPE
	SYNTAX INTEGER {
		false(0),
		true(1)
	}
	MAX-ACCESS read-only
	STATUS current
	DESCRIPTION
		"The state indicating whether or not to allow GTMD (Global Traffic Management
		Daemon) to handle DNS resolution for DNS queries and responses that contain
		Wide IP names."
	::= { ltmDnsProfileEntry 4 }

ltmDnsProfileDns64Mode OBJECT-TYPE
	SYNTAX INTEGER {
		disable(0),
		secondary(1),
		immediate(2),
		v4only(3)
	}
	MAX-ACCESS read-only
	STATUS current
	DESCRIPTION
		"The mode which specifies whether to perform DNS64 translation, and how
		to perform it.
		disable - no DNS64 translation is performed;
		secondary - send AAAA first, if no result send another A;
		immediate - send both AAAA and A together;
		v4only - send only A request."
	::= { ltmDnsProfileEntry 5 }

ltmDnsProfileDns64PrefixType OBJECT-TYPE
	SYNTAX InetAddressType
	MAX-ACCESS read-only
	STATUS current
	DESCRIPTION
		"The IP address type of DNS64 prefix."
	::= { ltmDnsProfileEntry 6 }

ltmDnsProfileDns64Prefix OBJECT-TYPE
	SYNTAX InetAddress
	MAX-ACCESS read-only
	STATUS current
	DESCRIPTION
		"The prefix for DNS64 mapping for the specified DNS profile."
	::= { ltmDnsProfileEntry 7 }

ltmDnsProfileDns64AdditionalRewrite OBJECT-TYPE
	SYNTAX INTEGER {
		disable(0),
		v6only(1),
		v4only(2),
		any(3)
	}
	MAX-ACCESS read-only
	STATUS current
	DESCRIPTION
		"Controls system behavior when a DNS response contains AAAA or A record(s)
		in the additional section. When DNS64 is enabled, this option selects how
		to rewrite (or not rewrite) these entries.
		disable - do not rewrite records in the additional section;
		v6only - the system deletes any A records in the additional section;
		v4only - the system deletes any AAAA records in the additional section,
		and rewrites A records into AAAA by prepending the IPv6 prefix;
		any - the system allows any AAAA records in the additional section, and
		rewrites A records into AAAA by prepending the IPv6 prefix."
	::= { ltmDnsProfileEntry 8 }

ltmDnsProfileDnsLastAction OBJECT-TYPE
	SYNTAX INTEGER {
		allow(0),
		drop(1),
		reject(2),
		hint(3),
		noerror(4)
	}
	MAX-ACCESS read-only
	STATUS current
	DESCRIPTION
		"Last action that will be taken if there is no matching zone name, i.e.
		a DNS query does not match a GTM Wide IP name, is not a DNSSEC query type
		(e.g. DNSKEY, etc.), does not match a DNS-Express Zone name, and DNS
		cache is not configured/enabled.
		allow - last action is to pass the DNS query to either a pool member
		or on-box BIND. This is pre-11.x behavior;
		drop - last action is to drop the DNS query;
		reject - last action is to send a DNS response with a REFUSED rcode
		set in the header;
		hint - last action is to send a DNS response with a list of root
		name servers;
		noerror - last action is to send a DNS response with a NOERROR rcode
		set in the header."
	::= { ltmDnsProfileEntry 9 }

ltmDnsProfileUseLocalBind OBJECT-TYPE
	SYNTAX INTEGER {
		false(0),
		true(1)
	}
	MAX-ACCESS read-only
	STATUS current
	DESCRIPTION
		"The state indicating whether or not local BIND is used as a DNS resource."
	::= { ltmDnsProfileEntry 10 }

ltmDnsProfileDnsExpressEnabled OBJECT-TYPE
	SYNTAX INTEGER {
		false(0),
		true(1)
	}
	MAX-ACCESS read-only
	STATUS current
	DESCRIPTION
		"The state indicating whether or not DNS Express is enabled for the
		specified profile."
	::= { ltmDnsProfileEntry 11 }

ltmDnsProfileDnssecEnabled OBJECT-TYPE
	SYNTAX INTEGER {
		false(0),
		true(1)
	}
	MAX-ACCESS read-only
	STATUS current
	DESCRIPTION
		"The state indicating whether or not DNSSEC is enabled for the specified
		profile."
	::= { ltmDnsProfileEntry 12 }

ltmDnsProfileCacheEnabled OBJECT-TYPE
	SYNTAX INTEGER {
		false(0),
		true(1)
	}
	MAX-ACCESS read-only
	STATUS current
	DESCRIPTION
		"The state indicating whether or not DNS cache is enabled for the specified
		profile."
	::= { ltmDnsProfileEntry 13 }

ltmDnsProfileDnsCache OBJECT-TYPE
	SYNTAX LongDisplayString
	MAX-ACCESS read-only
	STATUS current
	DESCRIPTION
		"The name of the DNS cache used for the specified profile."
	::= { ltmDnsProfileEntry 14 }

ltmDnsProfileProcessRd OBJECT-TYPE
	SYNTAX INTEGER {
		false(0),
		true(1)
	}
	MAX-ACCESS read-only
	STATUS current
	DESCRIPTION
		"The state indicating whether or not the further processing of clientside
		DNS packets with the RD (recursion desired) bit set in the header is
		allowed. If set to false, packet is subject to last action processing.
		This is for DDOS mitigation."
	::= { ltmDnsProfileEntry 15 }

ltmDnsProfileAvrDnsStatSampleRate OBJECT-TYPE
	SYNTAX Gauge
	MAX-ACCESS read-only
	STATUS current
	DESCRIPTION
		"The AVR DNS statistics sample rate for the specified profile. When
	        the value is 0, no DNS queries will be stored in analytics database.
	        When the value is 1, all DNS queries will be stored. When the value
	        is an integer N (N>1), only one DNS query for every N DNS queries will be stored."
	::= { ltmDnsProfileEntry 16 }

ltmDnsProfileSecurity OBJECT-TYPE
	SYNTAX LongDisplayString
	MAX-ACCESS read-only
	STATUS current
	DESCRIPTION
		"The name of the DNS security used for the specified profile."
	::= { ltmDnsProfileEntry 17 }

ltmDnsProfileSecurityEnabled OBJECT-TYPE
	SYNTAX INTEGER {
		false(0),
		true(1)
	}
	MAX-ACCESS read-only
	STATUS current
	DESCRIPTION
		"The state indicating whether or not DNS firewall is enabled for the specified
		profile."
	::= { ltmDnsProfileEntry 18 }

ltmDnsProfileLoggingProfile OBJECT-TYPE
	SYNTAX LongDisplayString
	MAX-ACCESS read-only
	STATUS current
	DESCRIPTION
		"The name of DNS logging profile that is being used."
	::= { ltmDnsProfileEntry 19 }

ltmDnsProfileLoggingEnabled OBJECT-TYPE
	SYNTAX INTEGER {
		false(0),
		true(1)
	}
	MAX-ACCESS read-only
	STATUS current
	DESCRIPTION
		"The state indicating whether or not DNS packet logging is enabled
	        for the specified profile."
	::= { ltmDnsProfileEntry 20 }

ltmDnsProfileFastDnsEnabled OBJECT-TYPE
	SYNTAX INTEGER {
		false(0),
		true(1)
	}
	MAX-ACCESS read-only
	STATUS current
	DESCRIPTION
		"The state indicating whether or not to allow DNS Rapid Response to handle DNS
	        resolution for DNS queries that contain GTM Wide IP names or part of a DNS-Express
	        Zone."
	::= { ltmDnsProfileEntry 21 }

ltmDnsProfileHwValidation OBJECT-TYPE
	SYNTAX INTEGER {
		false(0),
		true(1)
	}
	MAX-ACCESS read-only
	STATUS current
	DESCRIPTION
		"The state indicating whether or not to perform DNS query validation
	        in hardware."
	::= { ltmDnsProfileEntry 22 }

ltmDnsProfileHwCache OBJECT-TYPE
	SYNTAX INTEGER {
		false(0),
		true(1)
	}
	MAX-ACCESS read-only
	STATUS current
	DESCRIPTION
		"The state indicating whether or not to perform DNS response caching
	        in hardware and to generate responses for valid, matching DNS
	        queries."
	::= { ltmDnsProfileEntry 23 }

--==================================================================
-- Profile_httpclass
--==================================================================
ltmHttpClassNumber OBJECT-TYPE
	SYNTAX INTEGER
	MAX-ACCESS read-only
	STATUS	 deprecated
	DESCRIPTION
		"Deprecated!.
		The number of ltmHttpClassProfile entries in the table."
	::= { ltmHttpClassProfile 1 }

ltmHttpClassTable OBJECT-TYPE
	SYNTAX SEQUENCE OF LtmHttpClassEntry
	MAX-ACCESS not-accessible
	STATUS deprecated
	DESCRIPTION
		"Deprecated! A table containing information of HTTP class profile."
	::= { ltmHttpClassProfile 2 }

ltmHttpClassEntry OBJECT-TYPE
	SYNTAX  LtmHttpClassEntry
	MAX-ACCESS not-accessible
	STATUS deprecated
	DESCRIPTION
		"Columns in the ltmHttpClass Table"
	INDEX {
		ltmHttpClassName
	}
	::= { ltmHttpClassTable 1 }

LtmHttpClassEntry ::=
	SEQUENCE {
        	ltmHttpClassName                                          LongDisplayString,
        	ltmHttpClassConfigSource                                  INTEGER,
        	ltmHttpClassDefaultName                                   LongDisplayString,
        	ltmHttpClassPoolName                                      LongDisplayString,
        	ltmHttpClassAsmEnabled                                    INTEGER,
        	ltmHttpClassWaEnabled                                     INTEGER,
        	ltmHttpClassRedirectLocation                              LongDisplayString,
        	ltmHttpClassUrlRewrite                                    LongDisplayString
	}

ltmHttpClassName OBJECT-TYPE
	SYNTAX LongDisplayString
	MAX-ACCESS read-only
	STATUS	 deprecated
	DESCRIPTION
		"Deprecated! The name of a HTTP class profile."
	::= { ltmHttpClassEntry 1 }

ltmHttpClassConfigSource OBJECT-TYPE
	SYNTAX INTEGER {
		usercfg(0),
		basecfg(1)
	}
	MAX-ACCESS read-only
	STATUS	 deprecated
	DESCRIPTION
		"Deprecated! The state that specifies whether this is a base/pre-configured profile
		or user defined profile."
	::= { ltmHttpClassEntry 2 }

ltmHttpClassDefaultName OBJECT-TYPE
	SYNTAX LongDisplayString
	MAX-ACCESS read-only
	STATUS	 deprecated
	DESCRIPTION
		"Deprecated! The name of the profile from which the specified profile derives
		its attribute default values."
	::= { ltmHttpClassEntry 3 }

ltmHttpClassPoolName OBJECT-TYPE
	SYNTAX LongDisplayString
	MAX-ACCESS read-only
	STATUS	 deprecated
	DESCRIPTION
		"Deprecated! The pool name which will be used when the specified class matches."
	::= { ltmHttpClassEntry 4 }

ltmHttpClassAsmEnabled OBJECT-TYPE
	SYNTAX INTEGER {
		false(0),
		true(1)
	}
	MAX-ACCESS read-only
	STATUS	 deprecated
	DESCRIPTION
		"Deprecated! The state indicating whether this is an Application Security Module class or not."
	::= { ltmHttpClassEntry 5 }

ltmHttpClassWaEnabled OBJECT-TYPE
	SYNTAX INTEGER {
		false(0),
		true(1)
	}
	MAX-ACCESS read-only
	STATUS	 deprecated
	DESCRIPTION
		"Deprecated! The state indicating whether this is a Web Accelerator class or not."
	::= { ltmHttpClassEntry 6 }

ltmHttpClassRedirectLocation OBJECT-TYPE
	SYNTAX LongDisplayString
	MAX-ACCESS read-only
	STATUS	 deprecated
	DESCRIPTION
		"Deprecated! The string (which may include a TCL expression) to indicate where to
		redirect the original HTTP request once a match occurs."
	::= { ltmHttpClassEntry 7 }

ltmHttpClassUrlRewrite OBJECT-TYPE
	SYNTAX LongDisplayString
	MAX-ACCESS read-only
	STATUS	 deprecated
	DESCRIPTION
		"Deprecated! The string (which may include a TCL expression) with which to rewrite
		the URLs."
	::= { ltmHttpClassEntry 8 }

--==================================================================
-- Profile_httpclass_match_host
--==================================================================
ltmHttpClassHostNumber OBJECT-TYPE
	SYNTAX INTEGER
	MAX-ACCESS read-only
	STATUS	 deprecated
	DESCRIPTION
		"Deprecated!.
		The number of ltmHttpClassProfileHost entries in the table."
	::= { ltmHttpClassProfileHost 1 }

ltmHttpClassHostTable OBJECT-TYPE
	SYNTAX SEQUENCE OF LtmHttpClassHostEntry
	MAX-ACCESS not-accessible
	STATUS deprecated
	DESCRIPTION
		"Deprecated! A table containing information of host match patterns in HTTP class profiles."
	::= { ltmHttpClassProfileHost 2 }

ltmHttpClassHostEntry OBJECT-TYPE
	SYNTAX  LtmHttpClassHostEntry
	MAX-ACCESS not-accessible
	STATUS deprecated
	DESCRIPTION
		"Columns in the ltmHttpClassHost Table"
	INDEX {
		ltmHttpClassHostName,
		ltmHttpClassHostIndex
	}
	::= { ltmHttpClassHostTable 1 }

LtmHttpClassHostEntry ::=
	SEQUENCE {
        	ltmHttpClassHostName                                      LongDisplayString,
        	ltmHttpClassHostIndex                                     INTEGER,
        	ltmHttpClassHostString                                    LongDisplayString
	}

ltmHttpClassHostName OBJECT-TYPE
	SYNTAX LongDisplayString
	MAX-ACCESS read-only
	STATUS	 deprecated
	DESCRIPTION
		"Deprecated! The name of a HTTP class profile."
	::= { ltmHttpClassHostEntry 1 }

ltmHttpClassHostIndex OBJECT-TYPE
	SYNTAX INTEGER(0..2147483647)
	MAX-ACCESS read-only
	STATUS	 deprecated
	DESCRIPTION
		"Deprecated! The index of host match patterns for the specified HTTP class profile."
	::= { ltmHttpClassHostEntry 2 }

ltmHttpClassHostString OBJECT-TYPE
	SYNTAX LongDisplayString
	MAX-ACCESS read-only
	STATUS	 deprecated
	DESCRIPTION
		"Deprecated! The host match pattern for the specified profile."
	::= { ltmHttpClassHostEntry 3 }

--==================================================================
-- Profile_httpclass_match_path
--==================================================================
ltmHttpClassUriNumber OBJECT-TYPE
	SYNTAX INTEGER
	MAX-ACCESS read-only
	STATUS	 deprecated
	DESCRIPTION
		"Deprecated!.
		The number of ltmHttpClassProfileUri entries in the table."
	::= { ltmHttpClassProfileUri 1 }

ltmHttpClassUriTable OBJECT-TYPE
	SYNTAX SEQUENCE OF LtmHttpClassUriEntry
	MAX-ACCESS not-accessible
	STATUS deprecated
	DESCRIPTION
		"Deprecated! A table containing information of URI match patterns in HTTP class profiles."
	::= { ltmHttpClassProfileUri 2 }

ltmHttpClassUriEntry OBJECT-TYPE
	SYNTAX  LtmHttpClassUriEntry
	MAX-ACCESS not-accessible
	STATUS deprecated
	DESCRIPTION
		"Columns in the ltmHttpClassUri Table"
	INDEX {
		ltmHttpClassUriName,
		ltmHttpClassUriIndex
	}
	::= { ltmHttpClassUriTable 1 }

LtmHttpClassUriEntry ::=
	SEQUENCE {
        	ltmHttpClassUriName                                       LongDisplayString,
        	ltmHttpClassUriIndex                                      INTEGER,
        	ltmHttpClassUriString                                     LongDisplayString
	}

ltmHttpClassUriName OBJECT-TYPE
	SYNTAX LongDisplayString
	MAX-ACCESS read-only
	STATUS	 deprecated
	DESCRIPTION
		"Deprecated! The name of a HTTP class profile."
	::= { ltmHttpClassUriEntry 1 }

ltmHttpClassUriIndex OBJECT-TYPE
	SYNTAX INTEGER(0..2147483647)
	MAX-ACCESS read-only
	STATUS	 deprecated
	DESCRIPTION
		"Deprecated! The index of URI match patterns for the specified HTTP class profile."
	::= { ltmHttpClassUriEntry 2 }

ltmHttpClassUriString OBJECT-TYPE
	SYNTAX LongDisplayString
	MAX-ACCESS read-only
	STATUS	 deprecated
	DESCRIPTION
		"Deprecated! The URI match pattern for the specified profile."
	::= { ltmHttpClassUriEntry 3 }

--==================================================================
-- Profile_httpclass_match_header
--==================================================================
ltmHttpClassHeadNumber OBJECT-TYPE
	SYNTAX INTEGER
	MAX-ACCESS read-only
	STATUS	 deprecated
	DESCRIPTION
		"Deprecated!.
		The number of ltmHttpClassProfileHead entries in the table."
	::= { ltmHttpClassProfileHead 1 }

ltmHttpClassHeadTable OBJECT-TYPE
	SYNTAX SEQUENCE OF LtmHttpClassHeadEntry
	MAX-ACCESS not-accessible
	STATUS deprecated
	DESCRIPTION
		"Deprecated! A table containing information of HTTP request header match patterns in HTTP class profiles."
	::= { ltmHttpClassProfileHead 2 }

ltmHttpClassHeadEntry OBJECT-TYPE
	SYNTAX  LtmHttpClassHeadEntry
	MAX-ACCESS not-accessible
	STATUS deprecated
	DESCRIPTION
		"Columns in the ltmHttpClassHead Table"
	INDEX {
		ltmHttpClassHeadName,
		ltmHttpClassHeadIndex
	}
	::= { ltmHttpClassHeadTable 1 }

LtmHttpClassHeadEntry ::=
	SEQUENCE {
        	ltmHttpClassHeadName                                      LongDisplayString,
        	ltmHttpClassHeadIndex                                     INTEGER,
        	ltmHttpClassHeadString                                    LongDisplayString
	}

ltmHttpClassHeadName OBJECT-TYPE
	SYNTAX LongDisplayString
	MAX-ACCESS read-only
	STATUS	 deprecated
	DESCRIPTION
		"Deprecated! The name of a HTTP class profile."
	::= { ltmHttpClassHeadEntry 1 }

ltmHttpClassHeadIndex OBJECT-TYPE
	SYNTAX INTEGER(0..2147483647)
	MAX-ACCESS read-only
	STATUS	 deprecated
	DESCRIPTION
		"Deprecated! The index of HTTP request header match patterns for the specified HTTP class profile."
	::= { ltmHttpClassHeadEntry 2 }

ltmHttpClassHeadString OBJECT-TYPE
	SYNTAX LongDisplayString
	MAX-ACCESS read-only
	STATUS	 deprecated
	DESCRIPTION
		"Deprecated! The HTTP request header match pattern for the specified profile."
	::= { ltmHttpClassHeadEntry 3 }

--==================================================================
-- Profile_httpclass_match_cookies
--==================================================================
ltmHttpClassCookNumber OBJECT-TYPE
	SYNTAX INTEGER
	MAX-ACCESS read-only
	STATUS	 deprecated
	DESCRIPTION
		"Deprecated!.
		The number of ltmHttpClassProfileCook entries in the table."
	::= { ltmHttpClassProfileCook 1 }

ltmHttpClassCookTable OBJECT-TYPE
	SYNTAX SEQUENCE OF LtmHttpClassCookEntry
	MAX-ACCESS not-accessible
	STATUS deprecated
	DESCRIPTION
		"Deprecated! A table containing information of HTTP cookie match patterns in HTTP class profiles."
	::= { ltmHttpClassProfileCook 2 }

ltmHttpClassCookEntry OBJECT-TYPE
	SYNTAX  LtmHttpClassCookEntry
	MAX-ACCESS not-accessible
	STATUS deprecated
	DESCRIPTION
		"Columns in the ltmHttpClassCook Table"
	INDEX {
		ltmHttpClassCookName,
		ltmHttpClassCookIndex
	}
	::= { ltmHttpClassCookTable 1 }

LtmHttpClassCookEntry ::=
	SEQUENCE {
        	ltmHttpClassCookName                                      LongDisplayString,
        	ltmHttpClassCookIndex                                     INTEGER,
        	ltmHttpClassCookString                                    LongDisplayString
	}

ltmHttpClassCookName OBJECT-TYPE
	SYNTAX LongDisplayString
	MAX-ACCESS read-only
	STATUS	 deprecated
	DESCRIPTION
		"Deprecated! The name of a HTTP class profile."
	::= { ltmHttpClassCookEntry 1 }

ltmHttpClassCookIndex OBJECT-TYPE
	SYNTAX INTEGER(0..2147483647)
	MAX-ACCESS read-only
	STATUS	 deprecated
	DESCRIPTION
		"Deprecated! The index of HTTP cookie match patterns for the specified HTTP class profile."
	::= { ltmHttpClassCookEntry 2 }

ltmHttpClassCookString OBJECT-TYPE
	SYNTAX LongDisplayString
	MAX-ACCESS read-only
	STATUS	 deprecated
	DESCRIPTION
		"Deprecated! The HTTP cookie match pattern for the specified profile."
	::= { ltmHttpClassCookEntry 3 }

--==================================================================
-- Profile_httpclass_stat
--==================================================================
ltmHttpClassStatResetStats OBJECT-TYPE
	SYNTAX INTEGER
	MAX-ACCESS read-write
	STATUS	 deprecated
	DESCRIPTION
		"Deprecated!.
		The action to reset resettable statistics data in ltmHttpClassProfileStat.
		 Setting this value to 1 will reset statistics data.
		 Note, some statistics data may not be reset including data that are incremental counters."
	::= { ltmHttpClassProfileStat 1 }

ltmHttpClassStatNumber OBJECT-TYPE
	SYNTAX INTEGER
	MAX-ACCESS read-only
	STATUS	 deprecated
	DESCRIPTION
		"Deprecated!.
		The number of ltmHttpClassProfileStat entries in the table."
	::= { ltmHttpClassProfileStat 2 }

ltmHttpClassStatTable OBJECT-TYPE
	SYNTAX SEQUENCE OF LtmHttpClassStatEntry
	MAX-ACCESS not-accessible
	STATUS deprecated
	DESCRIPTION
		"Deprecated! A table containing statistics information of HTTP class profile."
	::= { ltmHttpClassProfileStat 3 }

ltmHttpClassStatEntry OBJECT-TYPE
	SYNTAX  LtmHttpClassStatEntry
	MAX-ACCESS not-accessible
	STATUS deprecated
	DESCRIPTION
		"Columns in the ltmHttpClassStat Table"
	INDEX {
		ltmHttpClassStatName
	}
	::= { ltmHttpClassStatTable 1 }

LtmHttpClassStatEntry ::=
	SEQUENCE {
        	ltmHttpClassStatName                                      LongDisplayString,
        	ltmHttpClassStatCookiePersistInserts                      Counter64,
        	ltmHttpClassStatResp2xxCnt                                Counter64,
        	ltmHttpClassStatResp3xxCnt                                Counter64,
        	ltmHttpClassStatResp4xxCnt                                Counter64,
        	ltmHttpClassStatResp5xxCnt                                Counter64,
        	ltmHttpClassStatNumberReqs                                Counter64,
        	ltmHttpClassStatGetReqs                                   Counter64,
        	ltmHttpClassStatPostReqs                                  Counter64,
        	ltmHttpClassStatV9Reqs                                    Counter64,
        	ltmHttpClassStatV10Reqs                                   Counter64,
        	ltmHttpClassStatV11Reqs                                   Counter64,
        	ltmHttpClassStatV9Resp                                    Counter64,
        	ltmHttpClassStatV10Resp                                   Counter64,
        	ltmHttpClassStatV11Resp                                   Counter64,
        	ltmHttpClassStatMaxKeepaliveReq                           Counter64,
        	ltmHttpClassStatRespBucket1k                              Counter64,
        	ltmHttpClassStatRespBucket4k                              Counter64,
        	ltmHttpClassStatRespBucket16k                             Counter64,
        	ltmHttpClassStatRespBucket32k                             Counter64,
        	ltmHttpClassStatRespBucket64k                             Counter64,
        	ltmHttpClassStatPrecompressBytes                          Counter64,
        	ltmHttpClassStatPostcompressBytes                         Counter64,
        	ltmHttpClassStatNullCompressBytes                         Counter64,
        	ltmHttpClassStatHtmlPrecompressBytes                      Counter64,
        	ltmHttpClassStatHtmlPostcompressBytes                     Counter64,
        	ltmHttpClassStatCssPrecompressBytes                       Counter64,
        	ltmHttpClassStatCssPostcompressBytes                      Counter64,
        	ltmHttpClassStatJsPrecompressBytes                        Counter64,
        	ltmHttpClassStatJsPostcompressBytes                       Counter64,
        	ltmHttpClassStatXmlPrecompressBytes                       Counter64,
        	ltmHttpClassStatXmlPostcompressBytes                      Counter64,
        	ltmHttpClassStatSgmlPrecompressBytes                      Counter64,
        	ltmHttpClassStatSgmlPostcompressBytes                     Counter64,
        	ltmHttpClassStatPlainPrecompressBytes                     Counter64,
        	ltmHttpClassStatPlainPostcompressBytes                    Counter64,
        	ltmHttpClassStatOctetPrecompressBytes                     Counter64,
        	ltmHttpClassStatOctetPostcompressBytes                    Counter64,
        	ltmHttpClassStatImagePrecompressBytes                     Counter64,
        	ltmHttpClassStatImagePostcompressBytes                    Counter64,
        	ltmHttpClassStatVideoPrecompressBytes                     Counter64,
        	ltmHttpClassStatVideoPostcompressBytes                    Counter64,
        	ltmHttpClassStatAudioPrecompressBytes                     Counter64,
        	ltmHttpClassStatAudioPostcompressBytes                    Counter64,
        	ltmHttpClassStatOtherPrecompressBytes                     Counter64,
        	ltmHttpClassStatOtherPostcompressBytes                    Counter64,
        	ltmHttpClassStatRamcacheHits                              Counter64,
        	ltmHttpClassStatRamcacheMisses                            Counter64,
        	ltmHttpClassStatRamcacheMissesAll                         Counter64,
        	ltmHttpClassStatRamcacheHitBytes                          Counter64,
        	ltmHttpClassStatRamcacheMissBytes                         Counter64,
        	ltmHttpClassStatRamcacheMissBytesAll                      Counter64
	}

ltmHttpClassStatName OBJECT-TYPE
	SYNTAX LongDisplayString
	MAX-ACCESS read-only
	STATUS	 deprecated
	DESCRIPTION
		"Deprecated! The name of a HTTP class profile."
	::= { ltmHttpClassStatEntry 1 }

ltmHttpClassStatCookiePersistInserts OBJECT-TYPE
	SYNTAX Counter64
	MAX-ACCESS read-only
	STATUS	 deprecated
	DESCRIPTION
		"Deprecated! The number of successful attempts to insert HTTP headers
		 for cookie persistence (set-cookie header insertions)."
	::= { ltmHttpClassStatEntry 2 }

ltmHttpClassStatResp2xxCnt OBJECT-TYPE
	SYNTAX Counter64
	MAX-ACCESS read-only
	STATUS	 deprecated
	DESCRIPTION
		"Deprecated! The number of server-side responses in range of 200 to 206
		 (successful responses)"
	::= { ltmHttpClassStatEntry 3 }

ltmHttpClassStatResp3xxCnt OBJECT-TYPE
	SYNTAX Counter64
	MAX-ACCESS read-only
	STATUS	 deprecated
	DESCRIPTION
		"Deprecated! The number of server-side responses in range of 300 to 307
		 (redirection responses)."
	::= { ltmHttpClassStatEntry 4 }

ltmHttpClassStatResp4xxCnt OBJECT-TYPE
	SYNTAX Counter64
	MAX-ACCESS read-only
	STATUS	 deprecated
	DESCRIPTION
		"Deprecated! The number of server-side responses in range of 400 to 417
		 (client errors)."
	::= { ltmHttpClassStatEntry 5 }

ltmHttpClassStatResp5xxCnt OBJECT-TYPE
	SYNTAX Counter64
	MAX-ACCESS read-only
	STATUS	 deprecated
	DESCRIPTION
		"Deprecated! The number of server-side responses in range of 500 to 505
		 (server errors)."
	::= { ltmHttpClassStatEntry 6 }

ltmHttpClassStatNumberReqs OBJECT-TYPE
	SYNTAX Counter64
	MAX-ACCESS read-only
	STATUS	 deprecated
	DESCRIPTION
		"Deprecated! The total number of HTTP requests."
	::= { ltmHttpClassStatEntry 7 }

ltmHttpClassStatGetReqs OBJECT-TYPE
	SYNTAX Counter64
	MAX-ACCESS read-only
	STATUS	 deprecated
	DESCRIPTION
		"Deprecated! The total number of HTTP get requests."
	::= { ltmHttpClassStatEntry 8 }

ltmHttpClassStatPostReqs OBJECT-TYPE
	SYNTAX Counter64
	MAX-ACCESS read-only
	STATUS	 deprecated
	DESCRIPTION
		"Deprecated! The total number of HTTP post requests."
	::= { ltmHttpClassStatEntry 9 }

ltmHttpClassStatV9Reqs OBJECT-TYPE
	SYNTAX Counter64
	MAX-ACCESS read-only
	STATUS	 deprecated
	DESCRIPTION
		"Deprecated! The total number of version 9 requests."
	::= { ltmHttpClassStatEntry 10 }

ltmHttpClassStatV10Reqs OBJECT-TYPE
	SYNTAX Counter64
	MAX-ACCESS read-only
	STATUS	 deprecated
	DESCRIPTION
		"Deprecated! The total number of version 10 requests."
	::= { ltmHttpClassStatEntry 11 }

ltmHttpClassStatV11Reqs OBJECT-TYPE
	SYNTAX Counter64
	MAX-ACCESS read-only
	STATUS	 deprecated
	DESCRIPTION
		"Deprecated! The total number of version 11 requests."
	::= { ltmHttpClassStatEntry 12 }

ltmHttpClassStatV9Resp OBJECT-TYPE
	SYNTAX Counter64
	MAX-ACCESS read-only
	STATUS	 deprecated
	DESCRIPTION
		"Deprecated! The total number of version 9 responses."
	::= { ltmHttpClassStatEntry 13 }

ltmHttpClassStatV10Resp OBJECT-TYPE
	SYNTAX Counter64
	MAX-ACCESS read-only
	STATUS	 deprecated
	DESCRIPTION
		"Deprecated! The total number of version 10 responses."
	::= { ltmHttpClassStatEntry 14 }

ltmHttpClassStatV11Resp OBJECT-TYPE
	SYNTAX Counter64
	MAX-ACCESS read-only
	STATUS	 deprecated
	DESCRIPTION
		"Deprecated! The total number of version 11 responses."
	::= { ltmHttpClassStatEntry 15 }

ltmHttpClassStatMaxKeepaliveReq OBJECT-TYPE
	SYNTAX Counter64
	MAX-ACCESS read-only
	STATUS	 deprecated
	DESCRIPTION
		"Deprecated! The maximum number of requests made in a connection."
	::= { ltmHttpClassStatEntry 16 }

ltmHttpClassStatRespBucket1k OBJECT-TYPE
	SYNTAX Counter64
	MAX-ACCESS read-only
	STATUS	 deprecated
	DESCRIPTION
		"Deprecated! The number of responses under 1k."
	::= { ltmHttpClassStatEntry 17 }

ltmHttpClassStatRespBucket4k OBJECT-TYPE
	SYNTAX Counter64
	MAX-ACCESS read-only
	STATUS	 deprecated
	DESCRIPTION
		"Deprecated! The number of responses between 1 - 4k."
	::= { ltmHttpClassStatEntry 18 }

ltmHttpClassStatRespBucket16k OBJECT-TYPE
	SYNTAX Counter64
	MAX-ACCESS read-only
	STATUS	 deprecated
	DESCRIPTION
		"Deprecated! The number of responses between 4 - 16k."
	::= { ltmHttpClassStatEntry 19 }

ltmHttpClassStatRespBucket32k OBJECT-TYPE
	SYNTAX Counter64
	MAX-ACCESS read-only
	STATUS	 deprecated
	DESCRIPTION
		"Deprecated! The number of responses between 16 - 32k."
	::= { ltmHttpClassStatEntry 20 }

ltmHttpClassStatRespBucket64k OBJECT-TYPE
	SYNTAX Counter64
	MAX-ACCESS read-only
	STATUS	 deprecated
	DESCRIPTION
		"Deprecated! Please use larger buckets"
	::= { ltmHttpClassStatEntry 21 }

ltmHttpClassStatPrecompressBytes OBJECT-TYPE
	SYNTAX Counter64
	MAX-ACCESS read-only
	STATUS	 deprecated
	DESCRIPTION
		"Deprecated! The number of response bytes before compression has taken place."
	::= { ltmHttpClassStatEntry 22 }

ltmHttpClassStatPostcompressBytes OBJECT-TYPE
	SYNTAX Counter64
	MAX-ACCESS read-only
	STATUS	 deprecated
	DESCRIPTION
		"Deprecated! The number of response bytes after compression has taken place."
	::= { ltmHttpClassStatEntry 23 }

ltmHttpClassStatNullCompressBytes OBJECT-TYPE
	SYNTAX Counter64
	MAX-ACCESS read-only
	STATUS	 deprecated
	DESCRIPTION
		"Deprecated! The number of bytes subjected to NULL compression (for license enforcement)."
	::= { ltmHttpClassStatEntry 24 }

ltmHttpClassStatHtmlPrecompressBytes OBJECT-TYPE
	SYNTAX Counter64
	MAX-ACCESS read-only
	STATUS	 deprecated
	DESCRIPTION
		"Deprecated! The number of pre-compressed bytes for the MIME-Types: HTML."
	::= { ltmHttpClassStatEntry 25 }

ltmHttpClassStatHtmlPostcompressBytes OBJECT-TYPE
	SYNTAX Counter64
	MAX-ACCESS read-only
	STATUS	 deprecated
	DESCRIPTION
		"Deprecated! The number of post-compressed bytes for the MIME-Types: HTML."
	::= { ltmHttpClassStatEntry 26 }

ltmHttpClassStatCssPrecompressBytes OBJECT-TYPE
	SYNTAX Counter64
	MAX-ACCESS read-only
	STATUS	 deprecated
	DESCRIPTION
		"Deprecated! The number of pre-compressed bytes for the MIME-Types: CSS."
	::= { ltmHttpClassStatEntry 27 }

ltmHttpClassStatCssPostcompressBytes OBJECT-TYPE
	SYNTAX Counter64
	MAX-ACCESS read-only
	STATUS	 deprecated
	DESCRIPTION
		"Deprecated! The number of post-compressed bytes for the MIME-Types: CSS."
	::= { ltmHttpClassStatEntry 28 }

ltmHttpClassStatJsPrecompressBytes OBJECT-TYPE
	SYNTAX Counter64
	MAX-ACCESS read-only
	STATUS	 deprecated
	DESCRIPTION
		"Deprecated! The number of pre-compressed bytes for the MIME-Types: Javascript."
	::= { ltmHttpClassStatEntry 29 }

ltmHttpClassStatJsPostcompressBytes OBJECT-TYPE
	SYNTAX Counter64
	MAX-ACCESS read-only
	STATUS	 deprecated
	DESCRIPTION
		"Deprecated! The number of post-compressed bytes for the MIME-Types: Javascript."
	::= { ltmHttpClassStatEntry 30 }

ltmHttpClassStatXmlPrecompressBytes OBJECT-TYPE
	SYNTAX Counter64
	MAX-ACCESS read-only
	STATUS	 deprecated
	DESCRIPTION
		"Deprecated! The number of pre-compressed bytes for the MIME-Types: XML."
	::= { ltmHttpClassStatEntry 31 }

ltmHttpClassStatXmlPostcompressBytes OBJECT-TYPE
	SYNTAX Counter64
	MAX-ACCESS read-only
	STATUS	 deprecated
	DESCRIPTION
		"Deprecated! The number of post-compressed bytes for the MIME-Types: XML."
	::= { ltmHttpClassStatEntry 32 }

ltmHttpClassStatSgmlPrecompressBytes OBJECT-TYPE
	SYNTAX Counter64
	MAX-ACCESS read-only
	STATUS	 deprecated
	DESCRIPTION
		"Deprecated! The number of pre-compressed bytes for the MIME-Types: SGML."
	::= { ltmHttpClassStatEntry 33 }

ltmHttpClassStatSgmlPostcompressBytes OBJECT-TYPE
	SYNTAX Counter64
	MAX-ACCESS read-only
	STATUS	 deprecated
	DESCRIPTION
		"Deprecated! The number of post-compressed bytes for the MIME-Types: SGML."
	::= { ltmHttpClassStatEntry 34 }

ltmHttpClassStatPlainPrecompressBytes OBJECT-TYPE
	SYNTAX Counter64
	MAX-ACCESS read-only
	STATUS	 deprecated
	DESCRIPTION
		"Deprecated! The number of pre-compressed bytes for the MIME-Types: Plain."
	::= { ltmHttpClassStatEntry 35 }

ltmHttpClassStatPlainPostcompressBytes OBJECT-TYPE
	SYNTAX Counter64
	MAX-ACCESS read-only
	STATUS	 deprecated
	DESCRIPTION
		"Deprecated! The number of post-compressed bytes for the MIME-Types: Plain."
	::= { ltmHttpClassStatEntry 36 }

ltmHttpClassStatOctetPrecompressBytes OBJECT-TYPE
	SYNTAX Counter64
	MAX-ACCESS read-only
	STATUS	 deprecated
	DESCRIPTION
		"Deprecated! The number of pre-compressed bytes for the MIME-Types: Octet stream."
	::= { ltmHttpClassStatEntry 37 }

ltmHttpClassStatOctetPostcompressBytes OBJECT-TYPE
	SYNTAX Counter64
	MAX-ACCESS read-only
	STATUS	 deprecated
	DESCRIPTION
		"Deprecated! The number of post-compressed bytes for the MIME-Types: Octet stream."
	::= { ltmHttpClassStatEntry 38 }

ltmHttpClassStatImagePrecompressBytes OBJECT-TYPE
	SYNTAX Counter64
	MAX-ACCESS read-only
	STATUS	 deprecated
	DESCRIPTION
		"Deprecated! The number of pre-compressed bytes for the MIME-Types: Images."
	::= { ltmHttpClassStatEntry 39 }

ltmHttpClassStatImagePostcompressBytes OBJECT-TYPE
	SYNTAX Counter64
	MAX-ACCESS read-only
	STATUS	 deprecated
	DESCRIPTION
		"Deprecated! The number of post-compressed bytes for the MIME-Types: Images."
	::= { ltmHttpClassStatEntry 40 }

ltmHttpClassStatVideoPrecompressBytes OBJECT-TYPE
	SYNTAX Counter64
	MAX-ACCESS read-only
	STATUS	 deprecated
	DESCRIPTION
		"Deprecated! The number of pre-compressed bytes for the MIME-Types: Video files."
	::= { ltmHttpClassStatEntry 41 }

ltmHttpClassStatVideoPostcompressBytes OBJECT-TYPE
	SYNTAX Counter64
	MAX-ACCESS read-only
	STATUS	 deprecated
	DESCRIPTION
		"Deprecated! The number of post-compressed bytes for the MIME-Types: Video files."
	::= { ltmHttpClassStatEntry 42 }

ltmHttpClassStatAudioPrecompressBytes OBJECT-TYPE
	SYNTAX Counter64
	MAX-ACCESS read-only
	STATUS	 deprecated
	DESCRIPTION
		"Deprecated! The number of pre-compressed bytes for the MIME-Types: Audio files."
	::= { ltmHttpClassStatEntry 43 }

ltmHttpClassStatAudioPostcompressBytes OBJECT-TYPE
	SYNTAX Counter64
	MAX-ACCESS read-only
	STATUS	 deprecated
	DESCRIPTION
		"Deprecated! The number of post-compressed bytes for the MIME-Types: Audio files."
	::= { ltmHttpClassStatEntry 44 }

ltmHttpClassStatOtherPrecompressBytes OBJECT-TYPE
	SYNTAX Counter64
	MAX-ACCESS read-only
	STATUS	 deprecated
	DESCRIPTION
		"Deprecated! The number of pre-compressed bytes for the MIME-Types: other than
		HTML, CSS, Javascript, XML, SGML, Plain, Images, Video files,
		Audio files."
	::= { ltmHttpClassStatEntry 45 }

ltmHttpClassStatOtherPostcompressBytes OBJECT-TYPE
	SYNTAX Counter64
	MAX-ACCESS read-only
	STATUS	 deprecated
	DESCRIPTION
		"Deprecated! The number of post-compressed bytes for the MIME-Types: other than
		HTML, CSS, Javascript, XML, SGML, Plain, Images, Video files,
		Audio files."
	::= { ltmHttpClassStatEntry 46 }

ltmHttpClassStatRamcacheHits OBJECT-TYPE
	SYNTAX Counter64
	MAX-ACCESS read-only
	STATUS	 deprecated
	DESCRIPTION
		"Deprecated! The number of RAM cache hits."
	::= { ltmHttpClassStatEntry 47 }

ltmHttpClassStatRamcacheMisses OBJECT-TYPE
	SYNTAX Counter64
	MAX-ACCESS read-only
	STATUS	 deprecated
	DESCRIPTION
		"Deprecated! The number of RAM cache misses, excluding un-cacheable data."
	::= { ltmHttpClassStatEntry 48 }

ltmHttpClassStatRamcacheMissesAll OBJECT-TYPE
	SYNTAX Counter64
	MAX-ACCESS read-only
	STATUS	 deprecated
	DESCRIPTION
		"Deprecated! The total number of RAM cache misses."
	::= { ltmHttpClassStatEntry 49 }

ltmHttpClassStatRamcacheHitBytes OBJECT-TYPE
	SYNTAX Counter64
	MAX-ACCESS read-only
	STATUS	 deprecated
	DESCRIPTION
		"Deprecated! The number of RAM cache hits in bytes."
	::= { ltmHttpClassStatEntry 50 }

ltmHttpClassStatRamcacheMissBytes OBJECT-TYPE
	SYNTAX Counter64
	MAX-ACCESS read-only
	STATUS	 deprecated
	DESCRIPTION
		"Deprecated! The number of RAM cache misses in bytes, excluding un-cacheable data."
	::= { ltmHttpClassStatEntry 51 }

ltmHttpClassStatRamcacheMissBytesAll OBJECT-TYPE
	SYNTAX Counter64
	MAX-ACCESS read-only
	STATUS	 deprecated
	DESCRIPTION
		"Deprecated! The total number of RAM cache misses in bytes."
	::= { ltmHttpClassStatEntry 52 }

--==================================================================
-- Profile_iiop
--==================================================================
ltmIiopProfileName OBJECT-TYPE
	SYNTAX LongDisplayString
	MAX-ACCESS read-only
	STATUS	 deprecated
	DESCRIPTION
		"Deprecated!.
		The name of a IIOP profile."
	::= { ltmIiopProfile 1 }

ltmIiopProfileConfigSource OBJECT-TYPE
	SYNTAX INTEGER {
		usercfg(0),
		basecfg(1)
	}
	MAX-ACCESS read-only
	STATUS	 deprecated
	DESCRIPTION
		"Deprecated!.
		The state that specifies whether this is a base/pre-configured profile
		or user defined profile."
	::= { ltmIiopProfile 2 }

ltmIiopProfileDefaultName OBJECT-TYPE
	SYNTAX LongDisplayString
	MAX-ACCESS read-only
	STATUS	 deprecated
	DESCRIPTION
		"Deprecated!.
		The name of the profile from which the specified profile derives
	        its attribute default values."
	::= { ltmIiopProfile 3 }

ltmIiopProfilePersistRequestId OBJECT-TYPE
	SYNTAX INTEGER {
		false(0),
		true(1)
	}
	MAX-ACCESS read-only
	STATUS	 deprecated
	DESCRIPTION
		"Deprecated!.
		The state that if true, persist the request ID."
	::= { ltmIiopProfile 4 }

ltmIiopProfilePersistObjectKey OBJECT-TYPE
	SYNTAX INTEGER {
		false(0),
		true(1)
	}
	MAX-ACCESS read-only
	STATUS	 deprecated
	DESCRIPTION
		"Deprecated!.
		The state that if true, persist the object key."
	::= { ltmIiopProfile 5 }

ltmIiopProfileAbortOnTimeout OBJECT-TYPE
	SYNTAX INTEGER {
		false(0),
		true(1)
	}
	MAX-ACCESS read-only
	STATUS	 deprecated
	DESCRIPTION
		"Deprecated!.
		The state that if true, abort the connection when response is
	        timed out."
	::= { ltmIiopProfile 6 }

ltmIiopProfileTimeout OBJECT-TYPE
	SYNTAX Gauge
	MAX-ACCESS read-only
	STATUS	 deprecated
	DESCRIPTION
		"Deprecated!.
		The response timeout for the specified IIOP profile."
	::= { ltmIiopProfile 7 }

--==================================================================
-- Profile_iiop_stat
--==================================================================
ltmIiopProfileStatResetStats OBJECT-TYPE
	SYNTAX INTEGER
	MAX-ACCESS read-write
	STATUS	 deprecated
	DESCRIPTION
		"Deprecated!.
		The action to reset resettable statistics data in ltmIiopProfileStat.
		 Setting this value to 1 will reset statistics data.
		 Note, some statistics data may not be reset including data that are incremental counters."
	::= { ltmIiopProfileStat 1 }

ltmIiopProfileStatName OBJECT-TYPE
	SYNTAX LongDisplayString
	MAX-ACCESS read-only
	STATUS	 deprecated
	DESCRIPTION
		"Deprecated!.
		The name of a IIOP profile."
	::= { ltmIiopProfileStat 2 }

ltmIiopProfileStatNumRequests OBJECT-TYPE
	SYNTAX Counter64
	MAX-ACCESS read-only
	STATUS	 deprecated
	DESCRIPTION
		"Deprecated!.
		The total number of IIOP requests."
	::= { ltmIiopProfileStat 3 }

ltmIiopProfileStatNumResponses OBJECT-TYPE
	SYNTAX Counter64
	MAX-ACCESS read-only
	STATUS	 deprecated
	DESCRIPTION
		"Deprecated!.
		The total number of IIOP responses."
	::= { ltmIiopProfileStat 4 }

ltmIiopProfileStatNumCancels OBJECT-TYPE
	SYNTAX Counter64
	MAX-ACCESS read-only
	STATUS	 deprecated
	DESCRIPTION
		"Deprecated!.
		The total number of IIOP cancel messages."
	::= { ltmIiopProfileStat 5 }

ltmIiopProfileStatNumErrors OBJECT-TYPE
	SYNTAX Counter64
	MAX-ACCESS read-only
	STATUS	 deprecated
	DESCRIPTION
		"Deprecated!.
		The total number of IIOP error messages."
	::= { ltmIiopProfileStat 6 }

ltmIiopProfileStatNumFragments OBJECT-TYPE
	SYNTAX Counter64
	MAX-ACCESS read-only
	STATUS	 deprecated
	DESCRIPTION
		"Deprecated!.
		The total number of IIOP fragments."
	::= { ltmIiopProfileStat 7 }

--==================================================================
-- Profile_rtsp
--==================================================================
ltmRtspProfileNumber OBJECT-TYPE
	SYNTAX INTEGER
	MAX-ACCESS read-only
	STATUS current
	DESCRIPTION
		"The number of ltmRtspProfile entries in the table."
	::= { ltmRtspProfile 1 }

ltmRtspProfileTable OBJECT-TYPE
	SYNTAX SEQUENCE OF LtmRtspProfileEntry
	MAX-ACCESS not-accessible
	STATUS current
	DESCRIPTION
		"A table containing information of RTSP profile."
	::= { ltmRtspProfile 2 }

ltmRtspProfileEntry OBJECT-TYPE
	SYNTAX  LtmRtspProfileEntry
	MAX-ACCESS not-accessible
	STATUS current
	DESCRIPTION
		"Columns in the ltmRtspProfile Table"
	INDEX {
		ltmRtspProfileName
	}
	::= { ltmRtspProfileTable 1 }

LtmRtspProfileEntry ::=
	SEQUENCE {
        	ltmRtspProfileName                                        LongDisplayString,
        	ltmRtspProfileConfigSource                                INTEGER,
        	ltmRtspProfileDefaultName                                 LongDisplayString,
        	ltmRtspProfileIdleTimeout                                 Gauge,
        	ltmRtspProfileMaxHeaderSize                               Gauge,
        	ltmRtspProfileMaxQueuedData                               Gauge,
        	ltmRtspProfileUnicastRedirect                             INTEGER,
        	ltmRtspProfileMulticastRedirect                           INTEGER,
        	ltmRtspProfileSessionReconnect                            INTEGER,
        	ltmRtspProfileRealHttpPersistence                         INTEGER,
        	ltmRtspProfileProxy                                       INTEGER,
        	ltmRtspProfileProxyHeader                                 LongDisplayString,
        	ltmRtspProfileRtpPort                                     InetPortNumber,
        	ltmRtspProfileRtcpPort                                    InetPortNumber,
        	ltmRtspProfileLogPublisher                                LongDisplayString,
        	ltmRtspProfileLogProfile                                  LongDisplayString
	}

ltmRtspProfileName OBJECT-TYPE
	SYNTAX LongDisplayString
	MAX-ACCESS read-only
	STATUS current
	DESCRIPTION
		"The name of a RTSP profile."
	::= { ltmRtspProfileEntry 1 }

ltmRtspProfileConfigSource OBJECT-TYPE
	SYNTAX INTEGER {
		usercfg(0),
		basecfg(1)
	}
	MAX-ACCESS read-only
	STATUS current
	DESCRIPTION
		"The state that specifies whether this is a base/pre-configured profile
		or user defined profile."
	::= { ltmRtspProfileEntry 2 }

ltmRtspProfileDefaultName OBJECT-TYPE
	SYNTAX LongDisplayString
	MAX-ACCESS read-only
	STATUS current
	DESCRIPTION
		"The name of the profile from which the specified profile derives
	        its attribute default values."
	::= { ltmRtspProfileEntry 3 }

ltmRtspProfileIdleTimeout OBJECT-TYPE
	SYNTAX Gauge
	MAX-ACCESS read-only
	STATUS current
	DESCRIPTION
		"The idle timeout (in seconds) for the specified RTSP profile."
	::= { ltmRtspProfileEntry 4 }

ltmRtspProfileMaxHeaderSize OBJECT-TYPE
	SYNTAX Gauge
	MAX-ACCESS read-only
	STATUS current
	DESCRIPTION
		"The maximum header size in bytes for the specified RTSP profile."
	::= { ltmRtspProfileEntry 5 }

ltmRtspProfileMaxQueuedData OBJECT-TYPE
	SYNTAX Gauge
	MAX-ACCESS read-only
	STATUS current
	DESCRIPTION
		"The maximum queued data in bytes for the specified RTSP profile."
	::= { ltmRtspProfileEntry 6 }

ltmRtspProfileUnicastRedirect OBJECT-TYPE
	SYNTAX INTEGER {
		false(0),
		true(1)
	}
	MAX-ACCESS read-only
	STATUS current
	DESCRIPTION
		"The state indicating whether unicast redirect is enable or not
		for the specified RTSP profile."
	::= { ltmRtspProfileEntry 7 }

ltmRtspProfileMulticastRedirect OBJECT-TYPE
	SYNTAX INTEGER {
		false(0),
		true(1)
	}
	MAX-ACCESS read-only
	STATUS current
	DESCRIPTION
		"The state indicating whether multicast redirect is enable or not
		for the specified RTSP profile."
	::= { ltmRtspProfileEntry 8 }

ltmRtspProfileSessionReconnect OBJECT-TYPE
	SYNTAX INTEGER {
		false(0),
		true(1)
	}
	MAX-ACCESS read-only
	STATUS current
	DESCRIPTION
		"The state indicating whether session reconnecting is enable or not
		for the specified RTSP profile."
	::= { ltmRtspProfileEntry 9 }

ltmRtspProfileRealHttpPersistence OBJECT-TYPE
	SYNTAX INTEGER {
		false(0),
		true(1)
	}
	MAX-ACCESS read-only
	STATUS current
	DESCRIPTION
		"The state indicating whether real HTTP persistence is enable or not
		for the specified RTSP profile."
	::= { ltmRtspProfileEntry 10 }

ltmRtspProfileProxy OBJECT-TYPE
	SYNTAX INTEGER {
		none(0),
		external(1),
		internal(2)
	}
	MAX-ACCESS read-only
	STATUS current
	DESCRIPTION
		"The proxy state for the specified RTSP profile."
	::= { ltmRtspProfileEntry 11 }

ltmRtspProfileProxyHeader OBJECT-TYPE
	SYNTAX LongDisplayString
	MAX-ACCESS read-only
	STATUS current
	DESCRIPTION
		"The proxy header for the specified RTSP profile."
	::= { ltmRtspProfileEntry 12 }

ltmRtspProfileRtpPort OBJECT-TYPE
	SYNTAX InetPortNumber
	MAX-ACCESS read-only
	STATUS current
	DESCRIPTION
		"The RTP port for the specified RTSP profile."
	::= { ltmRtspProfileEntry 13 }

ltmRtspProfileRtcpPort OBJECT-TYPE
	SYNTAX InetPortNumber
	MAX-ACCESS read-only
	STATUS current
	DESCRIPTION
		"The RTCP port for the specified RTSP profile."
	::= { ltmRtspProfileEntry 14 }

ltmRtspProfileLogPublisher OBJECT-TYPE
	SYNTAX LongDisplayString
	MAX-ACCESS read-only
	STATUS current
	DESCRIPTION
		"Specifies the name of the log publisher that logs ALG events, if any."
	::= { ltmRtspProfileEntry 15 }

ltmRtspProfileLogProfile OBJECT-TYPE
	SYNTAX LongDisplayString
	MAX-ACCESS read-only
	STATUS current
	DESCRIPTION
		"Specifies the name of the log profile that control the logging of ALG events, if any."
	::= { ltmRtspProfileEntry 16 }

--==================================================================
-- Profile_rtsp_stat
--==================================================================
ltmRtspProfileStatResetStats OBJECT-TYPE
	SYNTAX INTEGER
	MAX-ACCESS read-write
	STATUS current
	DESCRIPTION
		"The action to reset resettable statistics data in ltmRtspProfileStat.
		 Setting this value to 1 will reset statistics data.
		 Note, some statistics data may not be reset including data that are incremental counters."
	::= { ltmRtspProfileStat 1 }

ltmRtspProfileStatNumber OBJECT-TYPE
	SYNTAX INTEGER
	MAX-ACCESS read-only
	STATUS current
	DESCRIPTION
		"The number of ltmRtspProfileStat entries in the table."
	::= { ltmRtspProfileStat 2 }

ltmRtspProfileStatTable OBJECT-TYPE
	SYNTAX SEQUENCE OF LtmRtspProfileStatEntry
	MAX-ACCESS not-accessible
	STATUS current
	DESCRIPTION
		"A table containing statistic information of RTSP profile."
	::= { ltmRtspProfileStat 3 }

ltmRtspProfileStatEntry OBJECT-TYPE
	SYNTAX  LtmRtspProfileStatEntry
	MAX-ACCESS not-accessible
	STATUS current
	DESCRIPTION
		"Columns in the ltmRtspProfileStat Table"
	INDEX {
		ltmRtspProfileStatName
	}
	::= { ltmRtspProfileStatTable 1 }

LtmRtspProfileStatEntry ::=
	SEQUENCE {
        	ltmRtspProfileStatName                                    LongDisplayString,
        	ltmRtspProfileStatNumRequests                             Counter64,
        	ltmRtspProfileStatNumResponses                            Counter64,
        	ltmRtspProfileStatNumErrors                               Counter64,
        	ltmRtspProfileStatNumInterleaved                          Counter64
	}

ltmRtspProfileStatName OBJECT-TYPE
	SYNTAX LongDisplayString
	MAX-ACCESS read-only
	STATUS current
	DESCRIPTION
		"The name of a RTSP profile."
	::= { ltmRtspProfileStatEntry 1 }

ltmRtspProfileStatNumRequests OBJECT-TYPE
	SYNTAX Counter64
	MAX-ACCESS read-only
	STATUS current
	DESCRIPTION
		"The total number of RTSP requests for the specified RTSP profile."
	::= { ltmRtspProfileStatEntry 2 }

ltmRtspProfileStatNumResponses OBJECT-TYPE
	SYNTAX Counter64
	MAX-ACCESS read-only
	STATUS current
	DESCRIPTION
		"The total number of RTSP responses for the specified RTSP profile."
	::= { ltmRtspProfileStatEntry 3 }

ltmRtspProfileStatNumErrors OBJECT-TYPE
	SYNTAX Counter64
	MAX-ACCESS read-only
	STATUS current
	DESCRIPTION
		"The total number of RTSP errors for the specified RTSP profile."
	::= { ltmRtspProfileStatEntry 4 }

ltmRtspProfileStatNumInterleaved OBJECT-TYPE
	SYNTAX Counter64
	MAX-ACCESS read-only
	STATUS current
	DESCRIPTION
		"The total number of interleaved RTSP data packets for the specified RTSP profile."
	::= { ltmRtspProfileStatEntry 5 }

--==================================================================
-- Profile_sctp
--==================================================================
ltmSctpProfileNumber OBJECT-TYPE
	SYNTAX INTEGER
	MAX-ACCESS read-only
	STATUS current
	DESCRIPTION
		"The number of ltmSctpProfile entries in the table."
	::= { ltmSctpProfile 1 }

ltmSctpProfileTable OBJECT-TYPE
	SYNTAX SEQUENCE OF LtmSctpProfileEntry
	MAX-ACCESS not-accessible
	STATUS current
	DESCRIPTION
		"A table containing information of SCTP profile."
	::= { ltmSctpProfile 2 }

ltmSctpProfileEntry OBJECT-TYPE
	SYNTAX  LtmSctpProfileEntry
	MAX-ACCESS not-accessible
	STATUS current
	DESCRIPTION
		"Columns in the ltmSctpProfile Table"
	INDEX {
		ltmSctpProfileName
	}
	::= { ltmSctpProfileTable 1 }

LtmSctpProfileEntry ::=
	SEQUENCE {
        	ltmSctpProfileName                                        LongDisplayString,
        	ltmSctpProfileConfigSource                                INTEGER,
        	ltmSctpProfileDefaultName                                 LongDisplayString,
        	ltmSctpProfileRcvOrdered                                  INTEGER,
        	ltmSctpProfileSndPartial                                  INTEGER,
        	ltmSctpProfileTcpShutdown                                 INTEGER,
        	ltmSctpProfileResetOnTimeout                              INTEGER,
        	ltmSctpProfileOutStreams                                  Gauge,
        	ltmSctpProfileInStreams                                   Gauge,
        	ltmSctpProfileSndbuf                                      Gauge,
        	ltmSctpProfileRcvwnd                                      Gauge,
        	ltmSctpProfileTxChunks                                    Gauge,
        	ltmSctpProfileRxChunks                                    Gauge,
        	ltmSctpProfileCookieExpiration                            Gauge,
        	ltmSctpProfileInitMaxrtx                                  Gauge,
        	ltmSctpProfileAssocMaxrtx                                 Gauge,
        	ltmSctpProfileProxyBufferLow                              Gauge,
        	ltmSctpProfileProxyBufferHigh                             Gauge,
        	ltmSctpProfileIdleTimeout                                 Gauge,
        	ltmSctpProfileHeartbeatInterval                           Gauge,
        	ltmSctpProfileIpTosToPeer                                 INTEGER,
        	ltmSctpProfileLinkQosToPeer                               INTEGER,
        	ltmSctpProfileSecret                                      LongDisplayString,
        	ltmSctpProfileMaxBurst                                    Gauge,
        	ltmSctpProfileHeartbeatMaxBurst                           Gauge,
        	ltmSctpProfileMaxCommunicationPaths                       Gauge,
        	ltmSctpProfileMaxPathRetransmitLimit                      Gauge,
        	ltmSctpProfileServerSideMultihoming                       INTEGER,
        	ltmSctpProfileClientSideMultihoming                       INTEGER,
        	ltmSctpProfileRtoInitial                                  Gauge,
        	ltmSctpProfileRtoMin                                      Gauge,
        	ltmSctpProfileRtoMax                                      Gauge,
        	ltmSctpProfileSackTimeout                                 Gauge
	}

ltmSctpProfileName OBJECT-TYPE
	SYNTAX LongDisplayString
	MAX-ACCESS read-only
	STATUS current
	DESCRIPTION
		"The name of a SCTP profile."
	::= { ltmSctpProfileEntry 1 }

ltmSctpProfileConfigSource OBJECT-TYPE
	SYNTAX INTEGER {
		usercfg(0),
		basecfg(1)
	}
	MAX-ACCESS read-only
	STATUS current
	DESCRIPTION
		"The state that specifies whether this is a base/pre-configured profile
		or user defined profile."
	::= { ltmSctpProfileEntry 2 }

ltmSctpProfileDefaultName OBJECT-TYPE
	SYNTAX LongDisplayString
	MAX-ACCESS read-only
	STATUS current
	DESCRIPTION
		"The name of the profile from which the specified profile derives
	        its attribute default values."
	::= { ltmSctpProfileEntry 3 }

ltmSctpProfileRcvOrdered OBJECT-TYPE
	SYNTAX INTEGER {
		false(0),
		true(1)
	}
	MAX-ACCESS read-only
	STATUS current
	DESCRIPTION
		"The state indicating whether or not to in-order deliver messages to upper layer
		for the specified profile."
	::= { ltmSctpProfileEntry 4 }

ltmSctpProfileSndPartial OBJECT-TYPE
	SYNTAX INTEGER {
		false(0),
		true(1)
	}
	MAX-ACCESS read-only
	STATUS current
	DESCRIPTION
		"The state indicating whether or not to accept partial of application data
		for the specified profile."
	::= { ltmSctpProfileEntry 5 }

ltmSctpProfileTcpShutdown OBJECT-TYPE
	SYNTAX INTEGER {
		false(0),
		true(1)
	}
	MAX-ACCESS read-only
	STATUS current
	DESCRIPTION
		"The state indicating whether or not to emulate TCP closing
		for the specified profile."
	::= { ltmSctpProfileEntry 6 }

ltmSctpProfileResetOnTimeout OBJECT-TYPE
	SYNTAX INTEGER {
		false(0),
		true(1)
	}
	MAX-ACCESS read-only
	STATUS current
	DESCRIPTION
		"The state indicating whether or not reset connection when timeout
		for the specified profile."
	::= { ltmSctpProfileEntry 7 }

ltmSctpProfileOutStreams OBJECT-TYPE
	SYNTAX Gauge
	MAX-ACCESS read-only
	STATUS current
	DESCRIPTION
		"The total number of out-bound streams for the specified profile."
	::= { ltmSctpProfileEntry 8 }

ltmSctpProfileInStreams OBJECT-TYPE
	SYNTAX Gauge
	MAX-ACCESS read-only
	STATUS current
	DESCRIPTION
		"The total number of in-bound streams for the specified profile."
	::= { ltmSctpProfileEntry 9 }

ltmSctpProfileSndbuf OBJECT-TYPE
	SYNTAX Gauge
	MAX-ACCESS read-only
	STATUS current
	DESCRIPTION
		"The send buffer size in bytes for the specified profile."
	::= { ltmSctpProfileEntry 10 }

ltmSctpProfileRcvwnd OBJECT-TYPE
	SYNTAX Gauge
	MAX-ACCESS read-only
	STATUS current
	DESCRIPTION
		"The received window size, should be prorated to ltmSctpProfileRxChuncks
		for the specified profile."
	::= { ltmSctpProfileEntry 11 }

ltmSctpProfileTxChunks OBJECT-TYPE
	SYNTAX Gauge
	MAX-ACCESS read-only
	STATUS current
	DESCRIPTION
		"The number of sending chunk buffer for the specified profile."
	::= { ltmSctpProfileEntry 12 }

ltmSctpProfileRxChunks OBJECT-TYPE
	SYNTAX Gauge
	MAX-ACCESS read-only
	STATUS current
	DESCRIPTION
		"The number of receiving chunk buffer for the specified profile."
	::= { ltmSctpProfileEntry 13 }

ltmSctpProfileCookieExpiration OBJECT-TYPE
	SYNTAX Gauge
	MAX-ACCESS read-only
	STATUS current
	DESCRIPTION
		"The valid duration of cookie for the specified profile."
	::= { ltmSctpProfileEntry 14 }

ltmSctpProfileInitMaxrtx OBJECT-TYPE
	SYNTAX Gauge
	MAX-ACCESS read-only
	STATUS current
	DESCRIPTION
		"The maximum number of retries to establish a connection for the specified profile."
	::= { ltmSctpProfileEntry 15 }

ltmSctpProfileAssocMaxrtx OBJECT-TYPE
	SYNTAX Gauge
	MAX-ACCESS read-only
	STATUS current
	DESCRIPTION
		"The maximum number of retries to send data for the specified profile."
	::= { ltmSctpProfileEntry 16 }

ltmSctpProfileProxyBufferLow OBJECT-TYPE
	SYNTAX Gauge
	MAX-ACCESS read-only
	STATUS current
	DESCRIPTION
		"The proxy buffer level at which the receive window is opened
		for the specified profile."
	::= { ltmSctpProfileEntry 17 }

ltmSctpProfileProxyBufferHigh OBJECT-TYPE
	SYNTAX Gauge
	MAX-ACCESS read-only
	STATUS current
	DESCRIPTION
		"The proxy buffer level at which the receive window is closed
		for the specified profile."
	::= { ltmSctpProfileEntry 18 }

ltmSctpProfileIdleTimeout OBJECT-TYPE
	SYNTAX Gauge
	MAX-ACCESS read-only
	STATUS current
	DESCRIPTION
		"The number of seconds without traffic before a connection is eligible
		for deletion for the specified profile."
	::= { ltmSctpProfileEntry 19 }

ltmSctpProfileHeartbeatInterval OBJECT-TYPE
	SYNTAX Gauge
	MAX-ACCESS read-only
	STATUS current
	DESCRIPTION
		"The number of seconds to send heartbeat for the specified profile."
	::= { ltmSctpProfileEntry 20 }

ltmSctpProfileIpTosToPeer OBJECT-TYPE
	SYNTAX INTEGER
	MAX-ACCESS read-only
	STATUS current
	DESCRIPTION
		"The IP type of service set in packets sent to peer for the specified profile."
	::= { ltmSctpProfileEntry 21 }

ltmSctpProfileLinkQosToPeer OBJECT-TYPE
	SYNTAX INTEGER
	MAX-ACCESS read-only
	STATUS current
	DESCRIPTION
		"The link quality of service set in packets sent to peer for the specified profile."
	::= { ltmSctpProfileEntry 22 }

ltmSctpProfileSecret OBJECT-TYPE
	SYNTAX LongDisplayString
	MAX-ACCESS read-only
	STATUS	 deprecated
	DESCRIPTION
		"Deprecated! The internal secret string used to HMAC cookie for the specified profile."
	::= { ltmSctpProfileEntry 23 }

ltmSctpProfileMaxBurst OBJECT-TYPE
	SYNTAX Gauge
	MAX-ACCESS read-only
	STATUS current
	DESCRIPTION
		"The maximum number of data packets sent in a burst"
	::= { ltmSctpProfileEntry 24 }

ltmSctpProfileHeartbeatMaxBurst OBJECT-TYPE
	SYNTAX Gauge
	MAX-ACCESS read-only
	STATUS current
	DESCRIPTION
		"The maximum number of heartbeat packets sent in a burst"
	::= { ltmSctpProfileEntry 25 }

ltmSctpProfileMaxCommunicationPaths OBJECT-TYPE
	SYNTAX Gauge
	MAX-ACCESS read-only
	STATUS current
	DESCRIPTION
		"Maximum number of communication
	   paths."
	::= { ltmSctpProfileEntry 26 }

ltmSctpProfileMaxPathRetransmitLimit OBJECT-TYPE
	SYNTAX Gauge
	MAX-ACCESS read-only
	STATUS current
	DESCRIPTION
		"Limit of retransmission path."
	::= { ltmSctpProfileEntry 27 }

ltmSctpProfileServerSideMultihoming OBJECT-TYPE
	SYNTAX INTEGER {
		false(0),
		true(1)
	}
	MAX-ACCESS read-only
	STATUS current
	DESCRIPTION
		"Enables server
	   side multihoming."
	::= { ltmSctpProfileEntry 28 }

ltmSctpProfileClientSideMultihoming OBJECT-TYPE
	SYNTAX INTEGER {
		false(0),
		true(1)
	}
	MAX-ACCESS read-only
	STATUS current
	DESCRIPTION
		"Enables client
	   side multihoming."
	::= { ltmSctpProfileEntry 29 }

ltmSctpProfileRtoInitial OBJECT-TYPE
	SYNTAX Gauge
	MAX-ACCESS read-only
	STATUS current
	DESCRIPTION
		"This is the net.sctp.rto_initial configurable
	   parameter. It is the initial value of RTO(retransmission timeout)
	   that is used in RTO calculations. Unit of measurement is
	   milliseconds."
	::= { ltmSctpProfileEntry 30 }

ltmSctpProfileRtoMin OBJECT-TYPE
	SYNTAX Gauge
	MAX-ACCESS read-only
	STATUS current
	DESCRIPTION
		"This is the net.sctp.rto_min configurable
	   parameter. It is the minimum value of RTO(retransmission timeout)
	   that is used in RTO calculation. Unit of measurement is
	   milliseconds."
	::= { ltmSctpProfileEntry 31 }

ltmSctpProfileRtoMax OBJECT-TYPE
	SYNTAX Gauge
	MAX-ACCESS read-only
	STATUS current
	DESCRIPTION
		"This is the net.sctp.rto_max configurable
	   parameter. It is the maximum value of RTO(retransmission timeout)
	   that is used in RTO calculations. Unit of measurement is
	   milliseconds."
	::= { ltmSctpProfileEntry 32 }

ltmSctpProfileSackTimeout OBJECT-TYPE
	SYNTAX Gauge
	MAX-ACCESS read-only
	STATUS current
	DESCRIPTION
		"Delayed SACK timeout is configurable. Unit of
	   measurement is milliseconds."
	::= { ltmSctpProfileEntry 33 }

--==================================================================
-- Profile_sctp_stat
--==================================================================
ltmSctpProfileStatResetStats OBJECT-TYPE
	SYNTAX INTEGER
	MAX-ACCESS read-write
	STATUS current
	DESCRIPTION
		"The action to reset resettable statistics data in ltmSctpProfileStat.
		 Setting this value to 1 will reset statistics data.
		 Note, some statistics data may not be reset including data that are incremental counters."
	::= { ltmSctpProfileStat 1 }

ltmSctpProfileStatNumber OBJECT-TYPE
	SYNTAX INTEGER
	MAX-ACCESS read-only
	STATUS current
	DESCRIPTION
		"The number of ltmSctpProfileStat entries in the table."
	::= { ltmSctpProfileStat 2 }

ltmSctpProfileStatTable OBJECT-TYPE
	SYNTAX SEQUENCE OF LtmSctpProfileStatEntry
	MAX-ACCESS not-accessible
	STATUS current
	DESCRIPTION
		"A table containing statistic information of SCTP profile."
	::= { ltmSctpProfileStat 3 }

ltmSctpProfileStatEntry OBJECT-TYPE
	SYNTAX  LtmSctpProfileStatEntry
	MAX-ACCESS not-accessible
	STATUS current
	DESCRIPTION
		"Columns in the ltmSctpProfileStat Table"
	INDEX {
		ltmSctpProfileStatName
	}
	::= { ltmSctpProfileStatTable 1 }

LtmSctpProfileStatEntry ::=
	SEQUENCE {
        	ltmSctpProfileStatName                                    LongDisplayString,
        	ltmSctpProfileStatAccepts                                 Counter64,
        	ltmSctpProfileStatAcceptfails                             Counter64,
        	ltmSctpProfileStatConnects                                Counter64,
        	ltmSctpProfileStatConnfails                               Counter64,
        	ltmSctpProfileStatExpires                                 Counter64,
        	ltmSctpProfileStatAbandons                                Counter64,
        	ltmSctpProfileStatRxrst                                   Counter64,
        	ltmSctpProfileStatRxbadsum                                Counter64,
        	ltmSctpProfileStatRxcookie                                Counter64,
        	ltmSctpProfileStatRxbadcookie                             Counter64,
        	ltmSctpProfileStatAssociations                            Gauge,
        	ltmSctpProfileStatClosing                                 Gauge,
        	ltmSctpProfileStatConfirmedAddresses                      Gauge,
        	ltmSctpProfileStatUnconfirmedAddresses                    Gauge,
        	ltmSctpProfileStatActivePaths                             Gauge,
        	ltmSctpProfileStatInactivePaths                           Gauge
	}

ltmSctpProfileStatName OBJECT-TYPE
	SYNTAX LongDisplayString
	MAX-ACCESS read-only
	STATUS current
	DESCRIPTION
		"The name of a SCTP profile."
	::= { ltmSctpProfileStatEntry 1 }

ltmSctpProfileStatAccepts OBJECT-TYPE
	SYNTAX Counter64
	MAX-ACCESS read-only
	STATUS current
	DESCRIPTION
		"The total number of accepted connections for the specified profile."
	::= { ltmSctpProfileStatEntry 2 }

ltmSctpProfileStatAcceptfails OBJECT-TYPE
	SYNTAX Counter64
	MAX-ACCESS read-only
	STATUS current
	DESCRIPTION
		"The total number of not accepted responses for the specified profile."
	::= { ltmSctpProfileStatEntry 3 }

ltmSctpProfileStatConnects OBJECT-TYPE
	SYNTAX Counter64
	MAX-ACCESS read-only
	STATUS current
	DESCRIPTION
		"The total number of established connections for the specified profile."
	::= { ltmSctpProfileStatEntry 4 }

ltmSctpProfileStatConnfails OBJECT-TYPE
	SYNTAX Counter64
	MAX-ACCESS read-only
	STATUS current
	DESCRIPTION
		"The total number of connections failures for the specified profile."
	::= { ltmSctpProfileStatEntry 5 }

ltmSctpProfileStatExpires OBJECT-TYPE
	SYNTAX Counter64
	MAX-ACCESS read-only
	STATUS current
	DESCRIPTION
		"The total number of expired connections due to idle timeout for the specified profile."
	::= { ltmSctpProfileStatEntry 6 }

ltmSctpProfileStatAbandons OBJECT-TYPE
	SYNTAX Counter64
	MAX-ACCESS read-only
	STATUS current
	DESCRIPTION
		"The total number of abandoned connections due to retries/keep-alives for the specified profile."
	::= { ltmSctpProfileStatEntry 7 }

ltmSctpProfileStatRxrst OBJECT-TYPE
	SYNTAX Counter64
	MAX-ACCESS read-only
	STATUS current
	DESCRIPTION
		"The total number of received Abort chunks for the specified profile."
	::= { ltmSctpProfileStatEntry 8 }

ltmSctpProfileStatRxbadsum OBJECT-TYPE
	SYNTAX Counter64
	MAX-ACCESS read-only
	STATUS current
	DESCRIPTION
		"The total number of bad checksum in received packets for the specified profile."
	::= { ltmSctpProfileStatEntry 9 }

ltmSctpProfileStatRxcookie OBJECT-TYPE
	SYNTAX Counter64
	MAX-ACCESS read-only
	STATUS current
	DESCRIPTION
		"The total number of received SCTP cookies (including bad and good ones) for the specified profile."
	::= { ltmSctpProfileStatEntry 10 }

ltmSctpProfileStatRxbadcookie OBJECT-TYPE
	SYNTAX Counter64
	MAX-ACCESS read-only
	STATUS current
	DESCRIPTION
		"The total number of received bad SCTP cookies for the specified profile."
	::= { ltmSctpProfileStatEntry 11 }

ltmSctpProfileStatAssociations OBJECT-TYPE
	SYNTAX Gauge
	MAX-ACCESS read-only
	STATUS current
	DESCRIPTION
		"The current number of active SCTP associations for the specified profile."
	::= { ltmSctpProfileStatEntry 12 }

ltmSctpProfileStatClosing OBJECT-TYPE
	SYNTAX Gauge
	MAX-ACCESS read-only
	STATUS current
	DESCRIPTION
		"The current number of closing SCTP associations for the specified profile."
	::= { ltmSctpProfileStatEntry 13 }

ltmSctpProfileStatConfirmedAddresses OBJECT-TYPE
	SYNTAX Gauge
	MAX-ACCESS read-only
	STATUS current
	DESCRIPTION
		"The current number of confirmed remote transport addresses for the specified profile."
	::= { ltmSctpProfileStatEntry 14 }

ltmSctpProfileStatUnconfirmedAddresses OBJECT-TYPE
	SYNTAX Gauge
	MAX-ACCESS read-only
	STATUS current
	DESCRIPTION
		"The current number of unconfirmed remote transport addresses for the specified profile."
	::= { ltmSctpProfileStatEntry 15 }

ltmSctpProfileStatActivePaths OBJECT-TYPE
	SYNTAX Gauge
	MAX-ACCESS read-only
	STATUS current
	DESCRIPTION
		"The current number of active transport paths for the specified profile."
	::= { ltmSctpProfileStatEntry 16 }

ltmSctpProfileStatInactivePaths OBJECT-TYPE
	SYNTAX Gauge
	MAX-ACCESS read-only
	STATUS current
	DESCRIPTION
		"The current number of inactive transport paths for the specified profile."
	::= { ltmSctpProfileStatEntry 17 }

--==================================================================
-- Profile_statistics
--==================================================================
ltmUserStatProfileNumber OBJECT-TYPE
	SYNTAX INTEGER
	MAX-ACCESS read-only
	STATUS current
	DESCRIPTION
		"The number of ltmUserStatProfile entries in the table."
	::= { ltmUserStatProfile 1 }

ltmUserStatProfileTable OBJECT-TYPE
	SYNTAX SEQUENCE OF LtmUserStatProfileEntry
	MAX-ACCESS not-accessible
	STATUS current
	DESCRIPTION
		"A table containing basic information of user-defined statistics profiles.,
		The user can define up to 32 statistic fields in each profile.
		See ltmUserStatProfileStatTable for user-defined fields for each profile."
	::= { ltmUserStatProfile 2 }

ltmUserStatProfileEntry OBJECT-TYPE
	SYNTAX  LtmUserStatProfileEntry
	MAX-ACCESS not-accessible
	STATUS current
	DESCRIPTION
		"Columns in the ltmUserStatProfile Table"
	INDEX {
		ltmUserStatProfileName
	}
	::= { ltmUserStatProfileTable 1 }

LtmUserStatProfileEntry ::=
	SEQUENCE {
        	ltmUserStatProfileName                                    LongDisplayString,
        	ltmUserStatProfileConfigSource                            INTEGER,
        	ltmUserStatProfileDefaultName                             LongDisplayString
	}

ltmUserStatProfileName OBJECT-TYPE
	SYNTAX LongDisplayString
	MAX-ACCESS read-only
	STATUS current
	DESCRIPTION
		"The name of an user-defined statistics profile."
	::= { ltmUserStatProfileEntry 1 }

ltmUserStatProfileConfigSource OBJECT-TYPE
	SYNTAX INTEGER {
		usercfg(0),
		basecfg(1)
	}
	MAX-ACCESS read-only
	STATUS current
	DESCRIPTION
		"The state that specifies whether this is a base/pre-configured profile
		or user defined profile."
	::= { ltmUserStatProfileEntry 2 }

ltmUserStatProfileDefaultName OBJECT-TYPE
	SYNTAX LongDisplayString
	MAX-ACCESS read-only
	STATUS current
	DESCRIPTION
		"The name of the profile from which the specified profile derives
		its attribute default values."
	::= { ltmUserStatProfileEntry 3 }

--==================================================================
-- Profile_user_stat
--==================================================================
ltmUserStatProfileStatResetStats OBJECT-TYPE
	SYNTAX INTEGER
	MAX-ACCESS read-write
	STATUS current
	DESCRIPTION
		"The action to reset resettable statistics data in ltmUserStatProfileStat.
		 Setting this value to 1 will reset statistics data.
		 Note, some statistics data may not be reset including data that are incremental counters."
	::= { ltmUserStatProfileStat 1 }

ltmUserStatProfileStatNumber OBJECT-TYPE
	SYNTAX INTEGER
	MAX-ACCESS read-only
	STATUS current
	DESCRIPTION
		"The number of ltmUserStatProfileStat entries in the table."
	::= { ltmUserStatProfileStat 2 }

ltmUserStatProfileStatTable OBJECT-TYPE
	SYNTAX SEQUENCE OF LtmUserStatProfileStatEntry
	MAX-ACCESS not-accessible
	STATUS current
	DESCRIPTION
		"A table containing user-defined statistics information for related profiles.
		The maximum for user-defined statistic fields is 32 for each profile."
	::= { ltmUserStatProfileStat 3 }

ltmUserStatProfileStatEntry OBJECT-TYPE
	SYNTAX  LtmUserStatProfileStatEntry
	MAX-ACCESS not-accessible
	STATUS current
	DESCRIPTION
		"Columns in the ltmUserStatProfileStat Table"
	INDEX {
		ltmUserStatProfileStatName,
		ltmUserStatProfileStatFieldId
	}
	::= { ltmUserStatProfileStatTable 1 }

LtmUserStatProfileStatEntry ::=
	SEQUENCE {
        	ltmUserStatProfileStatName                                LongDisplayString,
        	ltmUserStatProfileStatFieldId                             INTEGER,
        	ltmUserStatProfileStatFieldName                           LongDisplayString,
        	ltmUserStatProfileStatFieldValue                          Counter64
	}

ltmUserStatProfileStatName OBJECT-TYPE
	SYNTAX LongDisplayString
	MAX-ACCESS read-only
	STATUS current
	DESCRIPTION
		"The name of an user-defined statistics profile."
	::= { ltmUserStatProfileStatEntry 1 }

ltmUserStatProfileStatFieldId OBJECT-TYPE
	SYNTAX INTEGER(0..2147483647)
	MAX-ACCESS read-only
	STATUS current
	DESCRIPTION
		"The index of the user-defined statistics field."
	::= { ltmUserStatProfileStatEntry 2 }

ltmUserStatProfileStatFieldName OBJECT-TYPE
	SYNTAX LongDisplayString
	MAX-ACCESS read-only
	STATUS current
	DESCRIPTION
		"The name of the related user-defined statistic field."
	::= { ltmUserStatProfileStatEntry 3 }

ltmUserStatProfileStatFieldValue OBJECT-TYPE
	SYNTAX Counter64
	MAX-ACCESS read-only
	STATUS current
	DESCRIPTION
		"The value of the related user-defined statistic field."
	::= { ltmUserStatProfileStatEntry 4 }

--==================================================================
-- Virtual_server_httpclass
--==================================================================
ltmVsHttpClassNumber OBJECT-TYPE
	SYNTAX INTEGER
	MAX-ACCESS read-only
	STATUS	 deprecated
	DESCRIPTION
		"Deprecated!.
		The number of ltmVirtualServHttpClass entries in the table."
	::= { ltmVirtualServHttpClass 1 }

ltmVsHttpClassTable OBJECT-TYPE
	SYNTAX SEQUENCE OF LtmVsHttpClassEntry
	MAX-ACCESS not-accessible
	STATUS deprecated
	DESCRIPTION
		"Deprecated! A table containing information of HTTP class profiles with which the specified virtual servers associate."
	::= { ltmVirtualServHttpClass 2 }

ltmVsHttpClassEntry OBJECT-TYPE
	SYNTAX  LtmVsHttpClassEntry
	MAX-ACCESS not-accessible
	STATUS deprecated
	DESCRIPTION
		"Columns in the ltmVsHttpClass Table"
	INDEX {
		ltmVsHttpClassVsName,
		ltmVsHttpClassProfileName
	}
	::= { ltmVsHttpClassTable 1 }

LtmVsHttpClassEntry ::=
	SEQUENCE {
        	ltmVsHttpClassVsName                                      LongDisplayString,
        	ltmVsHttpClassProfileName                                 LongDisplayString,
        	ltmVsHttpClassPriority                                    Gauge
	}

ltmVsHttpClassVsName OBJECT-TYPE
	SYNTAX LongDisplayString
	MAX-ACCESS read-only
	STATUS	 deprecated
	DESCRIPTION
		"Deprecated! The name of a virtual server."
	::= { ltmVsHttpClassEntry 1 }

ltmVsHttpClassProfileName OBJECT-TYPE
	SYNTAX LongDisplayString
	MAX-ACCESS read-only
	STATUS	 deprecated
	DESCRIPTION
		"Deprecated! The name of HTTP class profile with which the specified virtual server associate."
	::= { ltmVsHttpClassEntry 2 }

ltmVsHttpClassPriority OBJECT-TYPE
	SYNTAX Gauge
	MAX-ACCESS read-only
	STATUS	 deprecated
	DESCRIPTION
		"Deprecated! The priority of the profile among profiles used by the specified virtual server."
	::= { ltmVsHttpClassEntry 3 }

--==================================================================
-- Node_address_status
--==================================================================
ltmNodeAddrStatusNumber OBJECT-TYPE
	SYNTAX INTEGER
	MAX-ACCESS read-only
	STATUS current
	DESCRIPTION
		"The number of ltmNodeAddrStatus entries in the table."
	::= { ltmNodeAddrStatus 1 }

ltmNodeAddrStatusTable OBJECT-TYPE
	SYNTAX SEQUENCE OF LtmNodeAddrStatusEntry
	MAX-ACCESS not-accessible
	STATUS current
	DESCRIPTION
		"A table containing status information of node addresses."
	::= { ltmNodeAddrStatus 2 }

ltmNodeAddrStatusEntry OBJECT-TYPE
	SYNTAX  LtmNodeAddrStatusEntry
	MAX-ACCESS not-accessible
	STATUS current
	DESCRIPTION
		"Columns in the ltmNodeAddrStatus Table"
	INDEX {
		ltmNodeAddrStatusName
	}
	::= { ltmNodeAddrStatusTable 1 }

LtmNodeAddrStatusEntry ::=
	SEQUENCE {
        	ltmNodeAddrStatusAddrType                                 InetAddressType,
        	ltmNodeAddrStatusAddr                                     InetAddress,
        	ltmNodeAddrStatusAvailState                               INTEGER,
        	ltmNodeAddrStatusEnabledState                             INTEGER,
        	ltmNodeAddrStatusParentType                               Gauge,
        	ltmNodeAddrStatusDetailReason                             LongDisplayString,
        	ltmNodeAddrStatusName                                     LongDisplayString
	}

ltmNodeAddrStatusAddrType OBJECT-TYPE
	SYNTAX InetAddressType
	MAX-ACCESS read-only
	STATUS current
	DESCRIPTION
		"The IP address type of ltmNodeAddrStatusAddr."
	::= { ltmNodeAddrStatusEntry 1 }

ltmNodeAddrStatusAddr OBJECT-TYPE
	SYNTAX InetAddress
	MAX-ACCESS read-only
	STATUS current
	DESCRIPTION
		"The IP address of a node. It is interpreted within
		 the context of a ltmNodeAddrStatusAddrType value."
	::= { ltmNodeAddrStatusEntry 2 }

ltmNodeAddrStatusAvailState OBJECT-TYPE
	SYNTAX INTEGER {
		none(0),
		green(1),
		yellow(2),
		red(3),
		blue(4),
		gray(5)
	}
	MAX-ACCESS read-only
	STATUS current
	DESCRIPTION
		"The availability of the specified node address indicated in color.
		none - error;
		green - available in some capacity;
		yellow - not currently available;
		red - not available;
		blue - availability is unknown;
		gray - unlicensed."
	::= { ltmNodeAddrStatusEntry 3 }

ltmNodeAddrStatusEnabledState OBJECT-TYPE
	SYNTAX INTEGER {
		none(0),
		enabled(1),
		disabled(2),
		disabledbyparent(3)
	}
	MAX-ACCESS read-only
	STATUS current
	DESCRIPTION
		"The activity status of the specified node address, as specified
		by the user."
	::= { ltmNodeAddrStatusEntry 4 }

ltmNodeAddrStatusParentType OBJECT-TYPE
	SYNTAX Gauge
	MAX-ACCESS read-only
	STATUS	 deprecated
	DESCRIPTION
		"Deprecated! This is an internal data.
		The type of parent object which disabled the specified node address."
	::= { ltmNodeAddrStatusEntry 5 }

ltmNodeAddrStatusDetailReason OBJECT-TYPE
	SYNTAX LongDisplayString
	MAX-ACCESS read-only
	STATUS current
	DESCRIPTION
		"The detail description of the specified node's status."
	::= { ltmNodeAddrStatusEntry 6 }

ltmNodeAddrStatusName OBJECT-TYPE
	SYNTAX LongDisplayString
	MAX-ACCESS read-only
	STATUS current
	DESCRIPTION
		"node name."
	::= { ltmNodeAddrStatusEntry 7 }

--==================================================================
-- Pool_status
--==================================================================
ltmPoolStatusNumber OBJECT-TYPE
	SYNTAX INTEGER
	MAX-ACCESS read-only
	STATUS current
	DESCRIPTION
		"The number of ltmPoolStatus entries in the table."
	::= { ltmPoolStatus 1 }

ltmPoolStatusTable OBJECT-TYPE
	SYNTAX SEQUENCE OF LtmPoolStatusEntry
	MAX-ACCESS not-accessible
	STATUS current
	DESCRIPTION
		"A table containing status information of pools."
	::= { ltmPoolStatus 2 }

ltmPoolStatusEntry OBJECT-TYPE
	SYNTAX  LtmPoolStatusEntry
	MAX-ACCESS not-accessible
	STATUS current
	DESCRIPTION
		"Columns in the ltmPoolStatus Table"
	INDEX {
		ltmPoolStatusName
	}
	::= { ltmPoolStatusTable 1 }

LtmPoolStatusEntry ::=
	SEQUENCE {
        	ltmPoolStatusName                                         LongDisplayString,
        	ltmPoolStatusAvailState                                   INTEGER,
        	ltmPoolStatusEnabledState                                 INTEGER,
        	ltmPoolStatusParentType                                   Gauge,
        	ltmPoolStatusDetailReason                                 LongDisplayString
	}

ltmPoolStatusName OBJECT-TYPE
	SYNTAX LongDisplayString
	MAX-ACCESS read-only
	STATUS current
	DESCRIPTION
		"The name of a pool."
	::= { ltmPoolStatusEntry 1 }

ltmPoolStatusAvailState OBJECT-TYPE
	SYNTAX INTEGER {
		none(0),
		green(1),
		yellow(2),
		red(3),
		blue(4),
		grey(5)
	}
	MAX-ACCESS read-only
	STATUS current
	DESCRIPTION
		"The availability of the specified pool indicated in color.
		none - error;
		green - available in some capacity;
		yellow - not currently available;
		red - not available;
		blue - availability is unknown;
		gray - unlicensed"
	::= { ltmPoolStatusEntry 2 }

ltmPoolStatusEnabledState OBJECT-TYPE
	SYNTAX INTEGER {
		none(0),
		enabled(1),
		disabled(2),
		disabledbyparent(3)
	}
	MAX-ACCESS read-only
	STATUS current
	DESCRIPTION
		"The activity status of the specified pool, as specified
		by the user."
	::= { ltmPoolStatusEntry 3 }

ltmPoolStatusParentType OBJECT-TYPE
	SYNTAX Gauge
	MAX-ACCESS read-only
	STATUS	 deprecated
	DESCRIPTION
		"Deprecated! This is an internal data.
		The type of parent object which disabled the specified pool."
	::= { ltmPoolStatusEntry 4 }

ltmPoolStatusDetailReason OBJECT-TYPE
	SYNTAX LongDisplayString
	MAX-ACCESS read-only
	STATUS current
	DESCRIPTION
		"The detail description of the specified pool's status."
	::= { ltmPoolStatusEntry 5 }

--==================================================================
-- Pool_member_status
--==================================================================
ltmPoolMbrStatusNumber OBJECT-TYPE
	SYNTAX INTEGER
	MAX-ACCESS read-only
	STATUS current
	DESCRIPTION
		"The number of ltmPoolMemberStatus entries in the table."
	::= { ltmPoolMemberStatus 1 }

ltmPoolMbrStatusTable OBJECT-TYPE
	SYNTAX SEQUENCE OF LtmPoolMbrStatusEntry
	MAX-ACCESS not-accessible
	STATUS current
	DESCRIPTION
		"A table containing status information of pool members."
	::= { ltmPoolMemberStatus 2 }

ltmPoolMbrStatusEntry OBJECT-TYPE
	SYNTAX  LtmPoolMbrStatusEntry
	MAX-ACCESS not-accessible
	STATUS current
	DESCRIPTION
		"Columns in the ltmPoolMbrStatus Table"
	INDEX {
		ltmPoolMbrStatusPoolName,
		ltmPoolMbrStatusNodeName,
		ltmPoolMbrStatusPort
	}
	::= { ltmPoolMbrStatusTable 1 }

LtmPoolMbrStatusEntry ::=
	SEQUENCE {
        	ltmPoolMbrStatusPoolName                                  LongDisplayString,
        	ltmPoolMbrStatusAddrType                                  InetAddressType,
        	ltmPoolMbrStatusAddr                                      InetAddress,
        	ltmPoolMbrStatusPort                                      InetPortNumber,
        	ltmPoolMbrStatusAvailState                                INTEGER,
        	ltmPoolMbrStatusEnabledState                              INTEGER,
        	ltmPoolMbrStatusParentType                                Gauge,
        	ltmPoolMbrStatusDetailReason                              LongDisplayString,
        	ltmPoolMbrStatusNodeName                                  LongDisplayString
	}

ltmPoolMbrStatusPoolName OBJECT-TYPE
	SYNTAX LongDisplayString
	MAX-ACCESS read-only
	STATUS current
	DESCRIPTION
		"The name of a pool."
	::= { ltmPoolMbrStatusEntry 1 }

ltmPoolMbrStatusAddrType OBJECT-TYPE
	SYNTAX InetAddressType
	MAX-ACCESS read-only
	STATUS current
	DESCRIPTION
		"The IP address type of ltmPoolMbrStatusAddr."
	::= { ltmPoolMbrStatusEntry 2 }

ltmPoolMbrStatusAddr OBJECT-TYPE
	SYNTAX InetAddress
	MAX-ACCESS read-only
	STATUS current
	DESCRIPTION
		"The IP address of a pool member in the specified pool.
		It is interpreted within the context of an ltmPoolMbrStatusAddrType value."
	::= { ltmPoolMbrStatusEntry 3 }

ltmPoolMbrStatusPort OBJECT-TYPE
	SYNTAX InetPortNumber
	MAX-ACCESS read-only
	STATUS current
	DESCRIPTION
		"The port number of the specified pool member."
	::= { ltmPoolMbrStatusEntry 4 }

ltmPoolMbrStatusAvailState OBJECT-TYPE
	SYNTAX INTEGER {
		none(0),
		green(1),
		yellow(2),
		red(3),
		blue(4),
		gray(5)
	}
	MAX-ACCESS read-only
	STATUS current
	DESCRIPTION
		"The availability of the specified pool member indicated in color.
		none - error;
		green - available in some capacity;
		yellow - not currently available;
		red - not available;
		blue - availability is unknown;
		gray - unlicensed."
	::= { ltmPoolMbrStatusEntry 5 }

ltmPoolMbrStatusEnabledState OBJECT-TYPE
	SYNTAX INTEGER {
		none(0),
		enabled(1),
		disabled(2),
		disabledbyparent(3)
	}
	MAX-ACCESS read-only
	STATUS current
	DESCRIPTION
		"The activity status of the specified pool member, as specified
		by the user."
	::= { ltmPoolMbrStatusEntry 6 }

ltmPoolMbrStatusParentType OBJECT-TYPE
	SYNTAX Gauge
	MAX-ACCESS read-only
	STATUS	 deprecated
	DESCRIPTION
		"Deprecated! This is an internal data.
		The type of parent object which disabled the specified pool member."
	::= { ltmPoolMbrStatusEntry 7 }

ltmPoolMbrStatusDetailReason OBJECT-TYPE
	SYNTAX LongDisplayString
	MAX-ACCESS read-only
	STATUS current
	DESCRIPTION
		"The detail description of the specified pool member's status."
	::= { ltmPoolMbrStatusEntry 8 }

ltmPoolMbrStatusNodeName OBJECT-TYPE
	SYNTAX LongDisplayString
	MAX-ACCESS read-only
	STATUS current
	DESCRIPTION
		"Name of associated name."
	::= { ltmPoolMbrStatusEntry 9 }

--==================================================================
-- Virtual_server_status
--==================================================================
ltmVsStatusNumber OBJECT-TYPE
	SYNTAX INTEGER
	MAX-ACCESS read-only
	STATUS current
	DESCRIPTION
		"The number of ltmVirtualServStatus entries in the table."
	::= { ltmVirtualServStatus 1 }

ltmVsStatusTable OBJECT-TYPE
	SYNTAX SEQUENCE OF LtmVsStatusEntry
	MAX-ACCESS not-accessible
	STATUS current
	DESCRIPTION
		"A table containing status information of virtual servers."
	::= { ltmVirtualServStatus 2 }

ltmVsStatusEntry OBJECT-TYPE
	SYNTAX  LtmVsStatusEntry
	MAX-ACCESS not-accessible
	STATUS current
	DESCRIPTION
		"Columns in the ltmVsStatus Table"
	INDEX {
		ltmVsStatusName
	}
	::= { ltmVsStatusTable 1 }

LtmVsStatusEntry ::=
	SEQUENCE {
        	ltmVsStatusName                                           LongDisplayString,
        	ltmVsStatusAvailState                                     INTEGER,
        	ltmVsStatusEnabledState                                   INTEGER,
        	ltmVsStatusParentType                                     Gauge,
        	ltmVsStatusDetailReason                                   LongDisplayString
	}

ltmVsStatusName OBJECT-TYPE
	SYNTAX LongDisplayString
	MAX-ACCESS read-only
	STATUS current
	DESCRIPTION
		"The name of a virtual server."
	::= { ltmVsStatusEntry 1 }

ltmVsStatusAvailState OBJECT-TYPE
	SYNTAX INTEGER {
		none(0),
		green(1),
		yellow(2),
		red(3),
		blue(4),
		gray(5)
	}
	MAX-ACCESS read-only
	STATUS current
	DESCRIPTION
		"The availability of the specified virtual server indicated in color.
		none - error;
		green - available in some capacity;
		yellow - not currently available;
		red - not available;
		blue - availability is unknown;
		gray - unlicensed."
	::= { ltmVsStatusEntry 2 }

ltmVsStatusEnabledState OBJECT-TYPE
	SYNTAX INTEGER {
		none(0),
		enabled(1),
		disabled(2),
		disabledbyparent(3)
	}
	MAX-ACCESS read-only
	STATUS current
	DESCRIPTION
		"The activity status of the specified virtual server, as specified
		by the user."
	::= { ltmVsStatusEntry 3 }

ltmVsStatusParentType OBJECT-TYPE
	SYNTAX Gauge
	MAX-ACCESS read-only
	STATUS	 deprecated
	DESCRIPTION
		"Deprecated! This is an internal data.
		The type of parent object which disabled the specified virtual server."
	::= { ltmVsStatusEntry 4 }

ltmVsStatusDetailReason OBJECT-TYPE
	SYNTAX LongDisplayString
	MAX-ACCESS read-only
	STATUS current
	DESCRIPTION
		"The detail description of the specified virtual server's status."
	::= { ltmVsStatusEntry 5 }

--==================================================================
-- Virtual_address_status
--==================================================================
ltmVAddrStatusNumber OBJECT-TYPE
	SYNTAX INTEGER
	MAX-ACCESS read-only
	STATUS current
	DESCRIPTION
		"The number of ltmVirtualAddrStatus entries in the table."
	::= { ltmVirtualAddrStatus 1 }

ltmVAddrStatusTable OBJECT-TYPE
	SYNTAX SEQUENCE OF LtmVAddrStatusEntry
	MAX-ACCESS not-accessible
	STATUS current
	DESCRIPTION
		"A table containing status information of virtual addresses."
	::= { ltmVirtualAddrStatus 2 }

ltmVAddrStatusEntry OBJECT-TYPE
	SYNTAX  LtmVAddrStatusEntry
	MAX-ACCESS not-accessible
	STATUS current
	DESCRIPTION
		"Columns in the ltmVAddrStatus Table"
	INDEX {
		ltmVAddrStatusName
	}
	::= { ltmVAddrStatusTable 1 }

LtmVAddrStatusEntry ::=
	SEQUENCE {
        	ltmVAddrStatusAddrType                                    InetAddressType,
        	ltmVAddrStatusAddr                                        InetAddress,
        	ltmVAddrStatusAvailState                                  INTEGER,
        	ltmVAddrStatusEnabledState                                INTEGER,
        	ltmVAddrStatusParentType                                  Gauge,
        	ltmVAddrStatusDetailReason                                LongDisplayString,
        	ltmVAddrStatusName                                        LongDisplayString
	}

ltmVAddrStatusAddrType OBJECT-TYPE
	SYNTAX InetAddressType
	MAX-ACCESS read-only
	STATUS current
	DESCRIPTION
		"The IP address type of ltmVsAddrStatusAddr"
	::= { ltmVAddrStatusEntry 1 }

ltmVAddrStatusAddr OBJECT-TYPE
	SYNTAX InetAddress
	MAX-ACCESS read-only
	STATUS current
	DESCRIPTION
		"The IP address of a virtual address. It is interpreted
		 within the context of a ltmVsAddrAddrType value."
	::= { ltmVAddrStatusEntry 2 }

ltmVAddrStatusAvailState OBJECT-TYPE
	SYNTAX INTEGER {
		none(0),
		green(1),
		yellow(2),
		red(3),
		blue(4),
		gray(5)
	}
	MAX-ACCESS read-only
	STATUS current
	DESCRIPTION
		"The availability of the specified virtual address indicated in color.
		none - error;
		green - available in some capacity;
		yellow - not currently available;
		red - not available;
		blue - availability is unknown;
		gray - unlicensed."
	::= { ltmVAddrStatusEntry 3 }

ltmVAddrStatusEnabledState OBJECT-TYPE
	SYNTAX INTEGER {
		none(0),
		enabled(1),
		disabled(2),
		disabledbyparent(3)
	}
	MAX-ACCESS read-only
	STATUS current
	DESCRIPTION
		"The activity status of the specified virtual address, as specified
		by the user."
	::= { ltmVAddrStatusEntry 4 }

ltmVAddrStatusParentType OBJECT-TYPE
	SYNTAX Gauge
	MAX-ACCESS read-only
	STATUS	 deprecated
	DESCRIPTION
		"Deprecated! This is an internal data.
		The type of parent object which disabled the specified virtual address."
	::= { ltmVAddrStatusEntry 5 }

ltmVAddrStatusDetailReason OBJECT-TYPE
	SYNTAX LongDisplayString
	MAX-ACCESS read-only
	STATUS current
	DESCRIPTION
		"The detail description of the specified virtual address's status."
	::= { ltmVAddrStatusEntry 6 }

ltmVAddrStatusName OBJECT-TYPE
	SYNTAX LongDisplayString
	MAX-ACCESS read-only
	STATUS current
	DESCRIPTION
		"Virtual Address name"
	::= { ltmVAddrStatusEntry 7 }

--==================================================================
-- Profile_http_fallback_status_codes
--==================================================================
ltmFallbackStatusNumber OBJECT-TYPE
	SYNTAX INTEGER
	MAX-ACCESS read-only
	STATUS current
	DESCRIPTION
		"The number of ltmHttpProfileFallbackStatus entries in the table."
	::= { ltmHttpProfileFallbackStatus 1 }

ltmFallbackStatusTable OBJECT-TYPE
	SYNTAX SEQUENCE OF LtmFallbackStatusEntry
	MAX-ACCESS not-accessible
	STATUS current
	DESCRIPTION
		"A table containing information of status codes that when matched,
		traffic will be sent to the 'fallback_host' for HTTP profiles."
	::= { ltmHttpProfileFallbackStatus 2 }

ltmFallbackStatusEntry OBJECT-TYPE
	SYNTAX  LtmFallbackStatusEntry
	MAX-ACCESS not-accessible
	STATUS current
	DESCRIPTION
		"Columns in the ltmFallbackStatus Table"
	INDEX {
		ltmFallbackStatusName,
		ltmFallbackStatusIndex
	}
	::= { ltmFallbackStatusTable 1 }

LtmFallbackStatusEntry ::=
	SEQUENCE {
        	ltmFallbackStatusName                                     LongDisplayString,
        	ltmFallbackStatusIndex                                    INTEGER,
        	ltmFallbackStatusCode                                     LongDisplayString
	}

ltmFallbackStatusName OBJECT-TYPE
	SYNTAX LongDisplayString
	MAX-ACCESS read-only
	STATUS current
	DESCRIPTION
		"The name of a HTTP profile."
	::= { ltmFallbackStatusEntry 1 }

ltmFallbackStatusIndex OBJECT-TYPE
	SYNTAX INTEGER(0..2147483647)
	MAX-ACCESS read-only
	STATUS current
	DESCRIPTION
		"The index of status code for the specified HTTP profile."
	::= { ltmFallbackStatusEntry 2 }

ltmFallbackStatusCode OBJECT-TYPE
	SYNTAX LongDisplayString
	MAX-ACCESS read-only
	STATUS current
	DESCRIPTION
		"The status code that when matched, traffic will be sent to the 'fallback_host' for the specified profile."
	::= { ltmFallbackStatusEntry 3 }

--==================================================================
-- Profile_http_response_headers_permitted
--==================================================================
ltmRespHeadersPermNumber OBJECT-TYPE
	SYNTAX INTEGER
	MAX-ACCESS read-only
	STATUS current
	DESCRIPTION
		"The number of ltmHttpProfileRespHeadersPerm entries in the table."
	::= { ltmHttpProfileRespHeadersPerm 1 }

ltmRespHeadersPermTable OBJECT-TYPE
	SYNTAX SEQUENCE OF LtmRespHeadersPermEntry
	MAX-ACCESS not-accessible
	STATUS current
	DESCRIPTION
		"A table containing information of permitted headers in the
		responses for HTTP profiles."
	::= { ltmHttpProfileRespHeadersPerm 2 }

ltmRespHeadersPermEntry OBJECT-TYPE
	SYNTAX  LtmRespHeadersPermEntry
	MAX-ACCESS not-accessible
	STATUS current
	DESCRIPTION
		"Columns in the ltmRespHeadersPerm Table"
	INDEX {
		ltmRespHeadersPermName,
		ltmRespHeadersPermIndex
	}
	::= { ltmRespHeadersPermTable 1 }

LtmRespHeadersPermEntry ::=
	SEQUENCE {
        	ltmRespHeadersPermName                                    LongDisplayString,
        	ltmRespHeadersPermIndex                                   INTEGER,
        	ltmRespHeadersPermStr                                     LongDisplayString
	}

ltmRespHeadersPermName OBJECT-TYPE
	SYNTAX LongDisplayString
	MAX-ACCESS read-only
	STATUS current
	DESCRIPTION
		"The name of a HTTP profile."
	::= { ltmRespHeadersPermEntry 1 }

ltmRespHeadersPermIndex OBJECT-TYPE
	SYNTAX INTEGER(0..2147483647)
	MAX-ACCESS read-only
	STATUS current
	DESCRIPTION
		"The index of permitted header in a response for the specified HTTP profile."
	::= { ltmRespHeadersPermEntry 2 }

ltmRespHeadersPermStr OBJECT-TYPE
	SYNTAX LongDisplayString
	MAX-ACCESS read-only
	STATUS current
	DESCRIPTION
		"The permitted header in a response for the specified profile."
	::= { ltmRespHeadersPermEntry 3 }

--==================================================================
-- Profile_http_encrypt_cookies
--==================================================================
ltmEncCookiesNumber OBJECT-TYPE
	SYNTAX INTEGER
	MAX-ACCESS read-only
	STATUS current
	DESCRIPTION
		"The number of ltmHttpProfileEncCookies entries in the table."
	::= { ltmHttpProfileEncCookies 1 }

ltmEncCookiesTable OBJECT-TYPE
	SYNTAX SEQUENCE OF LtmEncCookiesEntry
	MAX-ACCESS not-accessible
	STATUS current
	DESCRIPTION
		"A table containing information of cookies to be encrypted before
		sending them to the clients for HTTP profiles."
	::= { ltmHttpProfileEncCookies 2 }

ltmEncCookiesEntry OBJECT-TYPE
	SYNTAX  LtmEncCookiesEntry
	MAX-ACCESS not-accessible
	STATUS current
	DESCRIPTION
		"Columns in the ltmEncCookies Table"
	INDEX {
		ltmEncCookiesName,
		ltmEncCookiesIndex
	}
	::= { ltmEncCookiesTable 1 }

LtmEncCookiesEntry ::=
	SEQUENCE {
        	ltmEncCookiesName                                         LongDisplayString,
        	ltmEncCookiesIndex                                        INTEGER,
        	ltmEncCookiesStr                                          LongDisplayString
	}

ltmEncCookiesName OBJECT-TYPE
	SYNTAX LongDisplayString
	MAX-ACCESS read-only
	STATUS current
	DESCRIPTION
		"The name of a HTTP profile."
	::= { ltmEncCookiesEntry 1 }

ltmEncCookiesIndex OBJECT-TYPE
	SYNTAX INTEGER(0..2147483647)
	MAX-ACCESS read-only
	STATUS current
	DESCRIPTION
		"The index of cookie to be encrypted before sending it to the client
		 for the specified HTTP profile."
	::= { ltmEncCookiesEntry 2 }

ltmEncCookiesStr OBJECT-TYPE
	SYNTAX LongDisplayString
	MAX-ACCESS read-only
	STATUS current
	DESCRIPTION
		"The cookie to be encrypted before sending it to the client
		for the specified profile."
	::= { ltmEncCookiesEntry 3 }

--==================================================================
-- Profile_bigproto_stat
--==================================================================
ltmFastL4ProfileStatResetStats OBJECT-TYPE
	SYNTAX INTEGER
	MAX-ACCESS read-write
	STATUS current
	DESCRIPTION
		"The action to reset resettable statistics data in ltmFastL4ProfileStat.
		 Setting this value to 1 will reset statistics data.
		 Note, some statistics data may not be reset including data that are incremental counters."
	::= { ltmFastL4ProfileStat 1 }

ltmFastL4ProfileStatNumber OBJECT-TYPE
	SYNTAX INTEGER
	MAX-ACCESS read-only
	STATUS current
	DESCRIPTION
		"The number of ltmFastL4ProfileStat entries in the table."
	::= { ltmFastL4ProfileStat 2 }

ltmFastL4ProfileStatTable OBJECT-TYPE
	SYNTAX SEQUENCE OF LtmFastL4ProfileStatEntry
	MAX-ACCESS not-accessible
	STATUS current
	DESCRIPTION
		"A table containing statistics information of fast L4 profiles."
	::= { ltmFastL4ProfileStat 3 }

ltmFastL4ProfileStatEntry OBJECT-TYPE
	SYNTAX  LtmFastL4ProfileStatEntry
	MAX-ACCESS not-accessible
	STATUS current
	DESCRIPTION
		"Columns in the ltmFastL4ProfileStat Table"
	INDEX {
		ltmFastL4ProfileStatName
	}
	::= { ltmFastL4ProfileStatTable 1 }

LtmFastL4ProfileStatEntry ::=
	SEQUENCE {
        	ltmFastL4ProfileStatName                                  LongDisplayString,
        	ltmFastL4ProfileStatOpen                                  Gauge,
        	ltmFastL4ProfileStatAccepts                               Counter64,
        	ltmFastL4ProfileStatAcceptfails                           Counter64,
        	ltmFastL4ProfileStatExpires                               Counter64,
        	ltmFastL4ProfileStatRxbadpkt                              Counter64,
        	ltmFastL4ProfileStatRxunreach                             Counter64,
        	ltmFastL4ProfileStatRxbadunreach                          Counter64,
        	ltmFastL4ProfileStatRxbadsum                              Counter64,
        	ltmFastL4ProfileStatTxerrors                              Counter64,
        	ltmFastL4ProfileStatSyncookIssue                          Counter64,
        	ltmFastL4ProfileStatSyncookAccept                         Counter64,
        	ltmFastL4ProfileStatSyncookReject                         Counter64,
        	ltmFastL4ProfileStatServersynrtx                          Counter64,
        	ltmFastL4ProfileStatLbcSuccessful                         Counter64,
        	ltmFastL4ProfileStatLbcTimedout                           Counter64
	}

ltmFastL4ProfileStatName OBJECT-TYPE
	SYNTAX LongDisplayString
	MAX-ACCESS read-only
	STATUS current
	DESCRIPTION
		"The name of a fast L4 profile."
	::= { ltmFastL4ProfileStatEntry 1 }

ltmFastL4ProfileStatOpen OBJECT-TYPE
	SYNTAX Gauge
	MAX-ACCESS read-only
	STATUS current
	DESCRIPTION
		"The number of current open connections for the specified fast L4 profile."
	::= { ltmFastL4ProfileStatEntry 2 }

ltmFastL4ProfileStatAccepts OBJECT-TYPE
	SYNTAX Counter64
	MAX-ACCESS read-only
	STATUS current
	DESCRIPTION
		"The number of accepted connections for the specified fast L4 profile."
	::= { ltmFastL4ProfileStatEntry 3 }

ltmFastL4ProfileStatAcceptfails OBJECT-TYPE
	SYNTAX Counter64
	MAX-ACCESS read-only
	STATUS current
	DESCRIPTION
		"The number of not accepted connections for the specified fast L4 profile."
	::= { ltmFastL4ProfileStatEntry 4 }

ltmFastL4ProfileStatExpires OBJECT-TYPE
	SYNTAX Counter64
	MAX-ACCESS read-only
	STATUS current
	DESCRIPTION
		"The number of expired connections due to idle timeout for the specified fast L4 profile."
	::= { ltmFastL4ProfileStatEntry 5 }

ltmFastL4ProfileStatRxbadpkt OBJECT-TYPE
	SYNTAX Counter64
	MAX-ACCESS read-only
	STATUS current
	DESCRIPTION
		"The number of malformed packets for the specified fast L4 profile."
	::= { ltmFastL4ProfileStatEntry 6 }

ltmFastL4ProfileStatRxunreach OBJECT-TYPE
	SYNTAX Counter64
	MAX-ACCESS read-only
	STATUS current
	DESCRIPTION
		"The number of received ICMP unreach/TCP RST for the specified fast L4 profile."
	::= { ltmFastL4ProfileStatEntry 7 }

ltmFastL4ProfileStatRxbadunreach OBJECT-TYPE
	SYNTAX Counter64
	MAX-ACCESS read-only
	STATUS current
	DESCRIPTION
		"The number of received TCP RST outside the current window for the specified fast L4 profile."
	::= { ltmFastL4ProfileStatEntry 8 }

ltmFastL4ProfileStatRxbadsum OBJECT-TYPE
	SYNTAX Counter64
	MAX-ACCESS read-only
	STATUS current
	DESCRIPTION
		"The number of bad checksum for the specified fast L4 profile."
	::= { ltmFastL4ProfileStatEntry 9 }

ltmFastL4ProfileStatTxerrors OBJECT-TYPE
	SYNTAX Counter64
	MAX-ACCESS read-only
	STATUS current
	DESCRIPTION
		"The number of transmit datagram errors for the specified fast L4 profile."
	::= { ltmFastL4ProfileStatEntry 10 }

ltmFastL4ProfileStatSyncookIssue OBJECT-TYPE
	SYNTAX Counter64
	MAX-ACCESS read-only
	STATUS current
	DESCRIPTION
		"The number of syncookies issued for the specified fast L4 profile."
	::= { ltmFastL4ProfileStatEntry 11 }

ltmFastL4ProfileStatSyncookAccept OBJECT-TYPE
	SYNTAX Counter64
	MAX-ACCESS read-only
	STATUS current
	DESCRIPTION
		"The number of syncookies accepted for the specified fast L4 profile."
	::= { ltmFastL4ProfileStatEntry 12 }

ltmFastL4ProfileStatSyncookReject OBJECT-TYPE
	SYNTAX Counter64
	MAX-ACCESS read-only
	STATUS current
	DESCRIPTION
		"The number of syncookies rejected for the specified fast L4 profile."
	::= { ltmFastL4ProfileStatEntry 13 }

ltmFastL4ProfileStatServersynrtx OBJECT-TYPE
	SYNTAX Counter64
	MAX-ACCESS read-only
	STATUS current
	DESCRIPTION
		"The number of retransmissions of SYN to server for a syncookied connection for the specified fast L4 profile."
	::= { ltmFastL4ProfileStatEntry 14 }

ltmFastL4ProfileStatLbcSuccessful OBJECT-TYPE
	SYNTAX Counter64
	MAX-ACCESS read-only
	STATUS current
	DESCRIPTION
		"The number of Successful Late Binding Connections."
	::= { ltmFastL4ProfileStatEntry 15 }

ltmFastL4ProfileStatLbcTimedout OBJECT-TYPE
	SYNTAX Counter64
	MAX-ACCESS read-only
	STATUS current
	DESCRIPTION
		"The number of Late Binding Connections that were timed out."
	::= { ltmFastL4ProfileStatEntry 16 }

--==================================================================
-- Profile_sipp
--==================================================================
ltmSipProfileNumber OBJECT-TYPE
	SYNTAX INTEGER
	MAX-ACCESS read-only
	STATUS current
	DESCRIPTION
		"The number of ltmSipProfile entries in the table."
	::= { ltmSipProfile 1 }

ltmSipProfileTable OBJECT-TYPE
	SYNTAX SEQUENCE OF LtmSipProfileEntry
	MAX-ACCESS not-accessible
	STATUS current
	DESCRIPTION
		"A table containing configuration information of SIP profiles."
	::= { ltmSipProfile 2 }

ltmSipProfileEntry OBJECT-TYPE
	SYNTAX  LtmSipProfileEntry
	MAX-ACCESS not-accessible
	STATUS current
	DESCRIPTION
		"Columns in the ltmSipProfile Table"
	INDEX {
		ltmSipProfileName
	}
	::= { ltmSipProfileTable 1 }

LtmSipProfileEntry ::=
	SEQUENCE {
        	ltmSipProfileName                                         LongDisplayString,
        	ltmSipProfileConfigSource                                 INTEGER,
        	ltmSipProfileDefaultName                                  LongDisplayString,
        	ltmSipProfileMaxSize                                      Gauge,
        	ltmSipProfileTerminateBye                                 INTEGER,
        	ltmSipProfileInsertVia                                    INTEGER,
        	ltmSipProfileSecureVia                                    INTEGER,
        	ltmSipProfileInsertRecordRoute                            INTEGER,
        	ltmSipProfileFirewallEnabled                              INTEGER,
        	ltmSipProfileLogPublisher                                 LongDisplayString,
        	ltmSipProfileLogProfile                                   LongDisplayString
	}

ltmSipProfileName OBJECT-TYPE
	SYNTAX LongDisplayString
	MAX-ACCESS read-only
	STATUS current
	DESCRIPTION
		"The name of a SIP profile."
	::= { ltmSipProfileEntry 1 }

ltmSipProfileConfigSource OBJECT-TYPE
	SYNTAX INTEGER {
		usercfg(0),
		basecfg(1)
	}
	MAX-ACCESS read-only
	STATUS current
	DESCRIPTION
		"The state that specifies whether this is a base/pre-configured profile
		or user defined profile."
	::= { ltmSipProfileEntry 2 }

ltmSipProfileDefaultName OBJECT-TYPE
	SYNTAX LongDisplayString
	MAX-ACCESS read-only
	STATUS current
	DESCRIPTION
		"The name of the profile from which the specified profile derives
		its attribute default values."
	::= { ltmSipProfileEntry 3 }

ltmSipProfileMaxSize OBJECT-TYPE
	SYNTAX Gauge
	MAX-ACCESS read-only
	STATUS current
	DESCRIPTION
		"The acceptable maximum SIP message size for the specified profile."
	::= { ltmSipProfileEntry 4 }

ltmSipProfileTerminateBye OBJECT-TYPE
	SYNTAX INTEGER {
		false(0),
		true(1)
	}
	MAX-ACCESS read-only
	STATUS current
	DESCRIPTION
		"The state indicating whether  or not to terminate connection after bye (200 BYE) message for the specified profile."
	::= { ltmSipProfileEntry 5 }

ltmSipProfileInsertVia OBJECT-TYPE
	SYNTAX INTEGER {
		false(0),
		true(1)
	}
	MAX-ACCESS read-only
	STATUS current
	DESCRIPTION
		"The state indicating whether or not to insert Via for the specified profile."
	::= { ltmSipProfileEntry 6 }

ltmSipProfileSecureVia OBJECT-TYPE
	SYNTAX INTEGER {
		false(0),
		true(1)
	}
	MAX-ACCESS read-only
	STATUS current
	DESCRIPTION
		"The state indicating whether or not it is SIPS/2.0/TLS for the specified profile."
	::= { ltmSipProfileEntry 7 }

ltmSipProfileInsertRecordRoute OBJECT-TYPE
	SYNTAX INTEGER {
		false(0),
		true(1)
	}
	MAX-ACCESS read-only
	STATUS current
	DESCRIPTION
		"The state indicating whether or not insert Record-route for the specified profile."
	::= { ltmSipProfileEntry 8 }

ltmSipProfileFirewallEnabled OBJECT-TYPE
	SYNTAX INTEGER {
		false(0),
		true(1)
	}
	MAX-ACCESS read-only
	STATUS current
	DESCRIPTION
		"The state indicating whether or not SIP firewall is enabled for the specified
		profile."
	::= { ltmSipProfileEntry 9 }

ltmSipProfileLogPublisher OBJECT-TYPE
	SYNTAX LongDisplayString
	MAX-ACCESS read-only
	STATUS current
	DESCRIPTION
		"Specifies the name of the log publisher that logs ALG events, if any."
	::= { ltmSipProfileEntry 10 }

ltmSipProfileLogProfile OBJECT-TYPE
	SYNTAX LongDisplayString
	MAX-ACCESS read-only
	STATUS current
	DESCRIPTION
		"Specifies the name of the log profile that control the logging of ALG events, if any."
	::= { ltmSipProfileEntry 11 }

--==================================================================
-- Profile_sipp_stat
--==================================================================
ltmSipProfileStatResetStats OBJECT-TYPE
	SYNTAX INTEGER
	MAX-ACCESS read-write
	STATUS current
	DESCRIPTION
		"The action to reset resettable statistics data in ltmSipProfileStat.
		 Setting this value to 1 will reset statistics data.
		 Note, some statistics data may not be reset including data that are incremental counters."
	::= { ltmSipProfileStat 1 }

ltmSipProfileStatNumber OBJECT-TYPE
	SYNTAX INTEGER
	MAX-ACCESS read-only
	STATUS current
	DESCRIPTION
		"The number of ltmSipProfileStat entries in the table."
	::= { ltmSipProfileStat 2 }

ltmSipProfileStatTable OBJECT-TYPE
	SYNTAX SEQUENCE OF LtmSipProfileStatEntry
	MAX-ACCESS not-accessible
	STATUS current
	DESCRIPTION
		"A table containing statistics information of SIP profiles."
	::= { ltmSipProfileStat 3 }

ltmSipProfileStatEntry OBJECT-TYPE
	SYNTAX  LtmSipProfileStatEntry
	MAX-ACCESS not-accessible
	STATUS current
	DESCRIPTION
		"Columns in the ltmSipProfileStat Table"
	INDEX {
		ltmSipProfileStatName
	}
	::= { ltmSipProfileStatTable 1 }

LtmSipProfileStatEntry ::=
	SEQUENCE {
        	ltmSipProfileStatName                                     LongDisplayString,
        	ltmSipProfileStatRequests                                 Counter64,
        	ltmSipProfileStatResponses                                Counter64,
        	ltmSipProfileStatBadmsgs                                  Counter64,
        	ltmSipProfileStatDrops                                    Counter64
	}

ltmSipProfileStatName OBJECT-TYPE
	SYNTAX LongDisplayString
	MAX-ACCESS read-only
	STATUS current
	DESCRIPTION
		"The name of a SIP profile."
	::= { ltmSipProfileStatEntry 1 }

ltmSipProfileStatRequests OBJECT-TYPE
	SYNTAX Counter64
	MAX-ACCESS read-only
	STATUS current
	DESCRIPTION
		"The total number of requests received for the specified profile."
	::= { ltmSipProfileStatEntry 2 }

ltmSipProfileStatResponses OBJECT-TYPE
	SYNTAX Counter64
	MAX-ACCESS read-only
	STATUS current
	DESCRIPTION
		"The total number of responses sent for the specified profile."
	::= { ltmSipProfileStatEntry 3 }

ltmSipProfileStatBadmsgs OBJECT-TYPE
	SYNTAX Counter64
	MAX-ACCESS read-only
	STATUS current
	DESCRIPTION
		"The total number of bad messages for the specified profile."
	::= { ltmSipProfileStatEntry 4 }

ltmSipProfileStatDrops OBJECT-TYPE
	SYNTAX Counter64
	MAX-ACCESS read-only
	STATUS current
	DESCRIPTION
		"The total number of dropped packets for the specified profile."
	::= { ltmSipProfileStatEntry 5 }

--==================================================================
-- Gtm_vs_score
--==================================================================
ltmVirtualModuleScoreNumber OBJECT-TYPE
	SYNTAX INTEGER
	MAX-ACCESS read-only
	STATUS current
	DESCRIPTION
		"The number of ltmVirtualModuleScore entries in the table."
	::= { ltmVirtualModuleScore 1 }

ltmVirtualModuleScoreTable OBJECT-TYPE
	SYNTAX SEQUENCE OF LtmVirtualModuleScoreEntry
	MAX-ACCESS not-accessible
	STATUS current
	DESCRIPTION
		"A table containing module capacity scores for virtual servers"
	::= { ltmVirtualModuleScore 2 }

ltmVirtualModuleScoreEntry OBJECT-TYPE
	SYNTAX  LtmVirtualModuleScoreEntry
	MAX-ACCESS not-accessible
	STATUS current
	DESCRIPTION
		"Columns in the ltmVirtualModuleScore Table"
	INDEX {
		ltmVirtualModuleScoreVsName,
		ltmVirtualModuleScoreModuleType
	}
	::= { ltmVirtualModuleScoreTable 1 }

LtmVirtualModuleScoreEntry ::=
	SEQUENCE {
        	ltmVirtualModuleScoreVsName                               LongDisplayString,
        	ltmVirtualModuleScoreModuleType                           INTEGER,
        	ltmVirtualModuleScoreScore                                Gauge
	}

ltmVirtualModuleScoreVsName OBJECT-TYPE
	SYNTAX LongDisplayString
	MAX-ACCESS read-only
	STATUS current
	DESCRIPTION
		"The name of the virtual server this score applies to."
	::= { ltmVirtualModuleScoreEntry 1 }

ltmVirtualModuleScoreModuleType OBJECT-TYPE
	SYNTAX INTEGER {
		asm(0),
		sam(1),
		wam(2)
	}
	MAX-ACCESS read-only
	STATUS current
	DESCRIPTION
		"The bigip module that this score applites to."
	::= { ltmVirtualModuleScoreEntry 2 }

ltmVirtualModuleScoreScore OBJECT-TYPE
	SYNTAX Gauge
	MAX-ACCESS read-only
	STATUS current
	DESCRIPTION
		"The score represents how much capacity the module estimates it has left."
	::= { ltmVirtualModuleScoreEntry 3 }

--==================================================================
-- Profile_isession
--==================================================================
ltmIsessionProfileNumber OBJECT-TYPE
	SYNTAX INTEGER
	MAX-ACCESS read-only
	STATUS current
	DESCRIPTION
		"The number of ltmIsessionProfile entries in the table."
	::= { ltmIsessionProfile 1 }

ltmIsessionProfileTable OBJECT-TYPE
	SYNTAX SEQUENCE OF LtmIsessionProfileEntry
	MAX-ACCESS not-accessible
	STATUS current
	DESCRIPTION
		"A table containing configuration information of Isession profiles."
	::= { ltmIsessionProfile 2 }

ltmIsessionProfileEntry OBJECT-TYPE
	SYNTAX  LtmIsessionProfileEntry
	MAX-ACCESS not-accessible
	STATUS current
	DESCRIPTION
		"Columns in the ltmIsessionProfile Table"
	INDEX {
		ltmIsessionProfileName
	}
	::= { ltmIsessionProfileTable 1 }

LtmIsessionProfileEntry ::=
	SEQUENCE {
        	ltmIsessionProfileName                                    LongDisplayString,
        	ltmIsessionProfileMode                                    INTEGER,
        	ltmIsessionProfileConnectionReuse                         INTEGER,
        	ltmIsessionProfileCompressionNull                         INTEGER,
        	ltmIsessionProfileCompressionDeflate                      INTEGER,
        	ltmIsessionProfileCompressionLzo                          INTEGER,
        	ltmIsessionProfileCompressionAdaptive                     INTEGER,
        	ltmIsessionProfileDeduplication                           INTEGER,
        	ltmIsessionProfilePortTransparency                        INTEGER,
        	ltmIsessionProfileTargetVirtual                           INTEGER,
        	ltmIsessionProfileEndpointPool                            LongDisplayString,
        	ltmIsessionProfileCompressionDeflateLevel                 Gauge,
        	ltmIsessionProfileCompressionBzip2                        INTEGER,
        	ltmIsessionProfileCompression                             INTEGER,
        	ltmIsessionProfileCompressionCodecs                       LongDisplayString
	}

ltmIsessionProfileName OBJECT-TYPE
	SYNTAX LongDisplayString
	MAX-ACCESS read-only
	STATUS current
	DESCRIPTION
		"The name of a iSession profile."
	::= { ltmIsessionProfileEntry 1 }

ltmIsessionProfileMode OBJECT-TYPE
	SYNTAX INTEGER {
		disabled(0),
		enabled(1)
	}
	MAX-ACCESS read-only
	STATUS current
	DESCRIPTION
		"Enable/disable this profile."
	::= { ltmIsessionProfileEntry 2 }

ltmIsessionProfileConnectionReuse OBJECT-TYPE
	SYNTAX INTEGER {
		disabled(0),
		enabled(1)
	}
	MAX-ACCESS read-only
	STATUS current
	DESCRIPTION
		"Enable/disable connection reuse."
	::= { ltmIsessionProfileEntry 3 }

ltmIsessionProfileCompressionNull OBJECT-TYPE
	SYNTAX INTEGER {
		disabled(0),
		enabled(1)
	}
	MAX-ACCESS read-only
	STATUS	 deprecated
	DESCRIPTION
		"Deprecated!
	         Select null compression method if enabled."
	::= { ltmIsessionProfileEntry 4 }

ltmIsessionProfileCompressionDeflate OBJECT-TYPE
	SYNTAX INTEGER {
		disabled(0),
		enabled(1)
	}
	MAX-ACCESS read-only
	STATUS	 deprecated
	DESCRIPTION
		"Deprecated!
	       Replaced by ltmIsessionCompression and ltmIsessionCompressionCodecs."
	::= { ltmIsessionProfileEntry 5 }

ltmIsessionProfileCompressionLzo OBJECT-TYPE
	SYNTAX INTEGER {
		disabled(0),
		enabled(1)
	}
	MAX-ACCESS read-only
	STATUS	 deprecated
	DESCRIPTION
		"Deprecated!
	       Replaced by ltmIsessionCompression and ltmIsessionCompressionCodecs."
	::= { ltmIsessionProfileEntry 6 }

ltmIsessionProfileCompressionAdaptive OBJECT-TYPE
	SYNTAX INTEGER {
		disabled(0),
		enabled(1)
	}
	MAX-ACCESS read-only
	STATUS current
	DESCRIPTION
		"Select adaptive compression method if enabled."
	::= { ltmIsessionProfileEntry 7 }

ltmIsessionProfileDeduplication OBJECT-TYPE
	SYNTAX INTEGER {
		disabled(0),
		enabled(1)
	}
	MAX-ACCESS read-only
	STATUS current
	DESCRIPTION
		"Enable/disable deduplication functionality."
	::= { ltmIsessionProfileEntry 8 }

ltmIsessionProfilePortTransparency OBJECT-TYPE
	SYNTAX INTEGER {
		disabled(0),
		enabled(1)
	}
	MAX-ACCESS read-only
	STATUS current
	DESCRIPTION
		"Use same destination port over WAN as specified by the client."
	::= { ltmIsessionProfileEntry 9 }

ltmIsessionProfileTargetVirtual OBJECT-TYPE
	SYNTAX INTEGER {
		none(0),
		hostmatchnoisession(1),
		hostmatchall(2),
		matchall(3)
	}
	MAX-ACCESS read-only
	STATUS current
	DESCRIPTION
		"Use to provide good match for targetted virtual."
	::= { ltmIsessionProfileEntry 10 }

ltmIsessionProfileEndpointPool OBJECT-TYPE
	SYNTAX LongDisplayString
	MAX-ACCESS read-only
	STATUS current
	DESCRIPTION
		"The name of a LTM pool for paired tunneling."
	::= { ltmIsessionProfileEntry 11 }

ltmIsessionProfileCompressionDeflateLevel OBJECT-TYPE
	SYNTAX Gauge
	MAX-ACCESS read-only
	STATUS current
	DESCRIPTION
		"Select compression level [1-9] when deflate compression method is enabled."
	::= { ltmIsessionProfileEntry 12 }

ltmIsessionProfileCompressionBzip2 OBJECT-TYPE
	SYNTAX INTEGER {
		disabled(0),
		enabled(1)
	}
	MAX-ACCESS read-only
	STATUS	 deprecated
	DESCRIPTION
		"Deprecated!
	        Replaced by ltmIsessionCompression and ltmIsessionCompressionCodecs."
	::= { ltmIsessionProfileEntry 13 }

ltmIsessionProfileCompression OBJECT-TYPE
	SYNTAX INTEGER {
		disabled(0),
		enabled(1)
	}
	MAX-ACCESS read-only
	STATUS current
	DESCRIPTION
		"Enable/disable compression functionality."
	::= { ltmIsessionProfileEntry 14 }

ltmIsessionProfileCompressionCodecs OBJECT-TYPE
	SYNTAX LongDisplayString
	MAX-ACCESS read-only
	STATUS current
	DESCRIPTION
		"Assign lzo(0), deflate(1), bzip2(2) comression methods, if compression enabled."
	::= { ltmIsessionProfileEntry 15 }

--==================================================================
-- Profile_isession_stat
--==================================================================
ltmIsessionProfileStatResetStats OBJECT-TYPE
	SYNTAX INTEGER
	MAX-ACCESS read-write
	STATUS current
	DESCRIPTION
		"The action to reset resettable statistics data in ltmIsessionProfileStat.
		 Setting this value to 1 will reset statistics data.
		 Note, some statistics data may not be reset including data that are incremental counters."
	::= { ltmIsessionProfileStat 1 }

ltmIsessionProfileStatNumber OBJECT-TYPE
	SYNTAX INTEGER
	MAX-ACCESS read-only
	STATUS current
	DESCRIPTION
		"The number of ltmIsessionProfileStat entries in the table."
	::= { ltmIsessionProfileStat 2 }

ltmIsessionProfileStatTable OBJECT-TYPE
	SYNTAX SEQUENCE OF LtmIsessionProfileStatEntry
	MAX-ACCESS not-accessible
	STATUS current
	DESCRIPTION
		"A table containing statistics information for virtual servers with iSession profiles"
	::= { ltmIsessionProfileStat 3 }

ltmIsessionProfileStatEntry OBJECT-TYPE
	SYNTAX  LtmIsessionProfileStatEntry
	MAX-ACCESS not-accessible
	STATUS current
	DESCRIPTION
		"Columns in the ltmIsessionProfileStat Table"
	INDEX {
		ltmIsessionProfileStatVsName
	}
	::= { ltmIsessionProfileStatTable 1 }

LtmIsessionProfileStatEntry ::=
	SEQUENCE {
        	ltmIsessionProfileStatVsName                              LongDisplayString,
        	ltmIsessionProfileStatProfileName                         LongDisplayString,
        	ltmIsessionProfileStatNullInUses                          Counter64,
        	ltmIsessionProfileStatNullInErrors                        Counter64,
        	ltmIsessionProfileStatNullInBytesOpt                      Counter64,
        	ltmIsessionProfileStatNullInBytesRaw                      Counter64,
        	ltmIsessionProfileStatNullOutUses                         Counter64,
        	ltmIsessionProfileStatNullOutErrors                       Counter64,
        	ltmIsessionProfileStatNullOutBytesOpt                     Counter64,
        	ltmIsessionProfileStatNullOutBytesRaw                     Counter64,
        	ltmIsessionProfileStatLzoInUses                           Counter64,
        	ltmIsessionProfileStatLzoInErrors                         Counter64,
        	ltmIsessionProfileStatLzoInBytesOpt                       Counter64,
        	ltmIsessionProfileStatLzoInBytesRaw                       Counter64,
        	ltmIsessionProfileStatLzoOutUses                          Counter64,
        	ltmIsessionProfileStatLzoOutErrors                        Counter64,
        	ltmIsessionProfileStatLzoOutBytesOpt                      Counter64,
        	ltmIsessionProfileStatLzoOutBytesRaw                      Counter64,
        	ltmIsessionProfileStatDeflateInUses                       Counter64,
        	ltmIsessionProfileStatDeflateInErrors                     Counter64,
        	ltmIsessionProfileStatDeflateInBytesOpt                   Counter64,
        	ltmIsessionProfileStatDeflateInBytesRaw                   Counter64,
        	ltmIsessionProfileStatDeflateOutUses                      Counter64,
        	ltmIsessionProfileStatDeflateOutErrors                    Counter64,
        	ltmIsessionProfileStatDeflateOutBytesOpt                  Counter64,
        	ltmIsessionProfileStatDeflateOutBytesRaw                  Counter64,
        	ltmIsessionProfileStatDedupInUses                         Counter64,
        	ltmIsessionProfileStatDedupInErrors                       Counter64,
        	ltmIsessionProfileStatDedupInBytesOpt                     Counter64,
        	ltmIsessionProfileStatDedupInBytesRaw                     Counter64,
        	ltmIsessionProfileStatDedupOutUses                        Counter64,
        	ltmIsessionProfileStatDedupOutErrors                      Counter64,
        	ltmIsessionProfileStatDedupOutBytesOpt                    Counter64,
        	ltmIsessionProfileStatDedupOutBytesRaw                    Counter64,
        	ltmIsessionProfileStatDedupInHits                         Counter64,
        	ltmIsessionProfileStatDedupInHitBytes                     Counter64,
        	ltmIsessionProfileStatDedupInHitHistBucket1k              Counter64,
        	ltmIsessionProfileStatDedupInHitHistBucket2k              Counter64,
        	ltmIsessionProfileStatDedupInHitHistBucket4k              Counter64,
        	ltmIsessionProfileStatDedupInHitHistBucket8k              Counter64,
        	ltmIsessionProfileStatDedupInHitHistBucket16k             Counter64,
        	ltmIsessionProfileStatDedupInHitHistBucket32k             Counter64,
        	ltmIsessionProfileStatDedupInHitHistBucket64k             Counter64,
        	ltmIsessionProfileStatDedupInHitHistBucket128k            Counter64,
        	ltmIsessionProfileStatDedupInHitHistBucket256k            Counter64,
        	ltmIsessionProfileStatDedupInHitHistBucket512k            Counter64,
        	ltmIsessionProfileStatDedupInHitHistBucket1m              Counter64,
        	ltmIsessionProfileStatDedupInHitHistBucketLarge           Counter64,
        	ltmIsessionProfileStatDedupInMisses                       Counter64,
        	ltmIsessionProfileStatDedupInMissBytes                    Counter64,
        	ltmIsessionProfileStatDedupInMissHistBucket1k             Counter64,
        	ltmIsessionProfileStatDedupInMissHistBucket2k             Counter64,
        	ltmIsessionProfileStatDedupInMissHistBucket4k             Counter64,
        	ltmIsessionProfileStatDedupInMissHistBucket8k             Counter64,
        	ltmIsessionProfileStatDedupInMissHistBucket16k            Counter64,
        	ltmIsessionProfileStatDedupInMissHistBucket32k            Counter64,
        	ltmIsessionProfileStatDedupInMissHistBucket64k            Counter64,
        	ltmIsessionProfileStatDedupInMissHistBucket128k           Counter64,
        	ltmIsessionProfileStatDedupInMissHistBucket256k           Counter64,
        	ltmIsessionProfileStatDedupInMissHistBucket512k           Counter64,
        	ltmIsessionProfileStatDedupInMissHistBucket1m             Counter64,
        	ltmIsessionProfileStatDedupInMissHistBucketLarge          Counter64,
        	ltmIsessionProfileStatDedupOutHits                        Counter64,
        	ltmIsessionProfileStatDedupOutHitBytes                    Counter64,
        	ltmIsessionProfileStatDedupOutHitHistBucket1k             Counter64,
        	ltmIsessionProfileStatDedupOutHitHistBucket2k             Counter64,
        	ltmIsessionProfileStatDedupOutHitHistBucket4k             Counter64,
        	ltmIsessionProfileStatDedupOutHitHistBucket8k             Counter64,
        	ltmIsessionProfileStatDedupOutHitHistBucket16k            Counter64,
        	ltmIsessionProfileStatDedupOutHitHistBucket32k            Counter64,
        	ltmIsessionProfileStatDedupOutHitHistBucket64k            Counter64,
        	ltmIsessionProfileStatDedupOutHitHistBucket128k           Counter64,
        	ltmIsessionProfileStatDedupOutHitHistBucket256k           Counter64,
        	ltmIsessionProfileStatDedupOutHitHistBucket512k           Counter64,
        	ltmIsessionProfileStatDedupOutHitHistBucket1m             Counter64,
        	ltmIsessionProfileStatDedupOutHitHistBucketLarge          Counter64,
        	ltmIsessionProfileStatDedupOutMisses                      Counter64,
        	ltmIsessionProfileStatDedupOutMissBytes                   Counter64,
        	ltmIsessionProfileStatDedupOutMissHistBucket1k            Counter64,
        	ltmIsessionProfileStatDedupOutMissHistBucket2k            Counter64,
        	ltmIsessionProfileStatDedupOutMissHistBucket4k            Counter64,
        	ltmIsessionProfileStatDedupOutMissHistBucket8k            Counter64,
        	ltmIsessionProfileStatDedupOutMissHistBucket16k           Counter64,
        	ltmIsessionProfileStatDedupOutMissHistBucket32k           Counter64,
        	ltmIsessionProfileStatDedupOutMissHistBucket64k           Counter64,
        	ltmIsessionProfileStatDedupOutMissHistBucket128k          Counter64,
        	ltmIsessionProfileStatDedupOutMissHistBucket256k          Counter64,
        	ltmIsessionProfileStatDedupOutMissHistBucket512k          Counter64,
        	ltmIsessionProfileStatDedupOutMissHistBucket1m            Counter64,
        	ltmIsessionProfileStatDedupOutMissHistBucketLarge         Counter64,
        	ltmIsessionProfileStatOutgoingConnsIdleCur                Gauge,
        	ltmIsessionProfileStatOutgoingConnsIdleMax                Counter64,
        	ltmIsessionProfileStatOutgoingConnsIdleTot                Counter64,
        	ltmIsessionProfileStatOutgoingConnsActiveCur              Gauge,
        	ltmIsessionProfileStatOutgoingConnsActiveMax              Counter64,
        	ltmIsessionProfileStatOutgoingConnsActiveTot              Counter64,
        	ltmIsessionProfileStatOutgoingConnsErrors                 Counter64,
        	ltmIsessionProfileStatOutgoingConnsPassthruTot            Counter64,
        	ltmIsessionProfileStatIncomingConnsActiveCur              Gauge,
        	ltmIsessionProfileStatIncomingConnsActiveMax              Counter64,
        	ltmIsessionProfileStatIncomingConnsActiveTot              Counter64,
        	ltmIsessionProfileStatIncomingConnsErrors                 Counter64,
        	ltmIsessionProfileStatBzip2InUses                         Counter64,
        	ltmIsessionProfileStatBzip2InErrors                       Counter64,
        	ltmIsessionProfileStatBzip2InBytesOpt                     Counter64,
        	ltmIsessionProfileStatBzip2InBytesRaw                     Counter64,
        	ltmIsessionProfileStatBzip2OutUses                        Counter64,
        	ltmIsessionProfileStatBzip2OutErrors                      Counter64,
        	ltmIsessionProfileStatBzip2OutBytesOpt                    Counter64,
        	ltmIsessionProfileStatBzip2OutBytesRaw                    Counter64
	}

ltmIsessionProfileStatVsName OBJECT-TYPE
	SYNTAX LongDisplayString
	MAX-ACCESS read-only
	STATUS current
	DESCRIPTION
		"The name of a iSession virtual server."
	::= { ltmIsessionProfileStatEntry 1 }

ltmIsessionProfileStatProfileName OBJECT-TYPE
	SYNTAX LongDisplayString
	MAX-ACCESS read-only
	STATUS current
	DESCRIPTION
		"The name of a iSession profile."
	::= { ltmIsessionProfileStatEntry 2 }

ltmIsessionProfileStatNullInUses OBJECT-TYPE
	SYNTAX Counter64
	MAX-ACCESS read-only
	STATUS current
	DESCRIPTION
		"The number of uses NULL compression for IN towards LAN"
	::= { ltmIsessionProfileStatEntry 3 }

ltmIsessionProfileStatNullInErrors OBJECT-TYPE
	SYNTAX Counter64
	MAX-ACCESS read-only
	STATUS current
	DESCRIPTION
		"The number of errors in use NULL compression for IN towards LAN"
	::= { ltmIsessionProfileStatEntry 4 }

ltmIsessionProfileStatNullInBytesOpt OBJECT-TYPE
	SYNTAX Counter64
	MAX-ACCESS read-only
	STATUS current
	DESCRIPTION
		"The number of opt bytes NULL compression for IN towards LAN"
	::= { ltmIsessionProfileStatEntry 5 }

ltmIsessionProfileStatNullInBytesRaw OBJECT-TYPE
	SYNTAX Counter64
	MAX-ACCESS read-only
	STATUS current
	DESCRIPTION
		"The number of raw bytes NULL compression for IN towards LAN"
	::= { ltmIsessionProfileStatEntry 6 }

ltmIsessionProfileStatNullOutUses OBJECT-TYPE
	SYNTAX Counter64
	MAX-ACCESS read-only
	STATUS current
	DESCRIPTION
		"The number of uses NULL compression for OUT towards WAN"
	::= { ltmIsessionProfileStatEntry 7 }

ltmIsessionProfileStatNullOutErrors OBJECT-TYPE
	SYNTAX Counter64
	MAX-ACCESS read-only
	STATUS current
	DESCRIPTION
		"The number of errors in use NULL compression for OUT towards WAN"
	::= { ltmIsessionProfileStatEntry 8 }

ltmIsessionProfileStatNullOutBytesOpt OBJECT-TYPE
	SYNTAX Counter64
	MAX-ACCESS read-only
	STATUS current
	DESCRIPTION
		"The number of opt bytes NULL compression for OUT towards WAN"
	::= { ltmIsessionProfileStatEntry 9 }

ltmIsessionProfileStatNullOutBytesRaw OBJECT-TYPE
	SYNTAX Counter64
	MAX-ACCESS read-only
	STATUS current
	DESCRIPTION
		"The number of raw bytes NULL compression for OUT towards WAN"
	::= { ltmIsessionProfileStatEntry 10 }

ltmIsessionProfileStatLzoInUses OBJECT-TYPE
	SYNTAX Counter64
	MAX-ACCESS read-only
	STATUS current
	DESCRIPTION
		"The number of uses LZO compression for IN towards LAN"
	::= { ltmIsessionProfileStatEntry 11 }

ltmIsessionProfileStatLzoInErrors OBJECT-TYPE
	SYNTAX Counter64
	MAX-ACCESS read-only
	STATUS current
	DESCRIPTION
		"The number of errors in use LZO compression for IN towards LAN"
	::= { ltmIsessionProfileStatEntry 12 }

ltmIsessionProfileStatLzoInBytesOpt OBJECT-TYPE
	SYNTAX Counter64
	MAX-ACCESS read-only
	STATUS current
	DESCRIPTION
		"The number of opt bytes LZO compression for IN towards LAN"
	::= { ltmIsessionProfileStatEntry 13 }

ltmIsessionProfileStatLzoInBytesRaw OBJECT-TYPE
	SYNTAX Counter64
	MAX-ACCESS read-only
	STATUS current
	DESCRIPTION
		"The number of raw bytes LZO compression for IN towards LAN"
	::= { ltmIsessionProfileStatEntry 14 }

ltmIsessionProfileStatLzoOutUses OBJECT-TYPE
	SYNTAX Counter64
	MAX-ACCESS read-only
	STATUS current
	DESCRIPTION
		"The number of uses LZO compression for OUT towards WAN"
	::= { ltmIsessionProfileStatEntry 15 }

ltmIsessionProfileStatLzoOutErrors OBJECT-TYPE
	SYNTAX Counter64
	MAX-ACCESS read-only
	STATUS current
	DESCRIPTION
		"The number of errors in use LZO compression for OUT towards WAN"
	::= { ltmIsessionProfileStatEntry 16 }

ltmIsessionProfileStatLzoOutBytesOpt OBJECT-TYPE
	SYNTAX Counter64
	MAX-ACCESS read-only
	STATUS current
	DESCRIPTION
		"The number of opt bytes LZO compression for OUT towards WAN"
	::= { ltmIsessionProfileStatEntry 17 }

ltmIsessionProfileStatLzoOutBytesRaw OBJECT-TYPE
	SYNTAX Counter64
	MAX-ACCESS read-only
	STATUS current
	DESCRIPTION
		"The number of raw bytes LZO compression for OUT towards WAN"
	::= { ltmIsessionProfileStatEntry 18 }

ltmIsessionProfileStatDeflateInUses OBJECT-TYPE
	SYNTAX Counter64
	MAX-ACCESS read-only
	STATUS current
	DESCRIPTION
		"The number of uses DEFLATE compression for IN towards LAN"
	::= { ltmIsessionProfileStatEntry 19 }

ltmIsessionProfileStatDeflateInErrors OBJECT-TYPE
	SYNTAX Counter64
	MAX-ACCESS read-only
	STATUS current
	DESCRIPTION
		"The number of errors in use DEFLATE compression for IN towards LAN"
	::= { ltmIsessionProfileStatEntry 20 }

ltmIsessionProfileStatDeflateInBytesOpt OBJECT-TYPE
	SYNTAX Counter64
	MAX-ACCESS read-only
	STATUS current
	DESCRIPTION
		"The number of opt bytes DEFLATE compression for IN towards LAN"
	::= { ltmIsessionProfileStatEntry 21 }

ltmIsessionProfileStatDeflateInBytesRaw OBJECT-TYPE
	SYNTAX Counter64
	MAX-ACCESS read-only
	STATUS current
	DESCRIPTION
		"The number of raw bytes DEFLATE compression for IN towards LAN"
	::= { ltmIsessionProfileStatEntry 22 }

ltmIsessionProfileStatDeflateOutUses OBJECT-TYPE
	SYNTAX Counter64
	MAX-ACCESS read-only
	STATUS current
	DESCRIPTION
		"The number of uses DEFLATE compression for OUT towards WAN"
	::= { ltmIsessionProfileStatEntry 23 }

ltmIsessionProfileStatDeflateOutErrors OBJECT-TYPE
	SYNTAX Counter64
	MAX-ACCESS read-only
	STATUS current
	DESCRIPTION
		"The number of errors in use DEFLATE compression for OUT towards WAN"
	::= { ltmIsessionProfileStatEntry 24 }

ltmIsessionProfileStatDeflateOutBytesOpt OBJECT-TYPE
	SYNTAX Counter64
	MAX-ACCESS read-only
	STATUS current
	DESCRIPTION
		"The number of opt bytes DEFLATE compression for OUT towards WAN"
	::= { ltmIsessionProfileStatEntry 25 }

ltmIsessionProfileStatDeflateOutBytesRaw OBJECT-TYPE
	SYNTAX Counter64
	MAX-ACCESS read-only
	STATUS current
	DESCRIPTION
		"The number of raw bytes DEFLATE compression for OUT towards WAN"
	::= { ltmIsessionProfileStatEntry 26 }

ltmIsessionProfileStatDedupInUses OBJECT-TYPE
	SYNTAX Counter64
	MAX-ACCESS read-only
	STATUS current
	DESCRIPTION
		"The number of uses DEDUPLICATION compression for IN towards LAN"
	::= { ltmIsessionProfileStatEntry 27 }

ltmIsessionProfileStatDedupInErrors OBJECT-TYPE
	SYNTAX Counter64
	MAX-ACCESS read-only
	STATUS current
	DESCRIPTION
		"The number of errors in use DEDUPLICATION compression for IN towards LAN"
	::= { ltmIsessionProfileStatEntry 28 }

ltmIsessionProfileStatDedupInBytesOpt OBJECT-TYPE
	SYNTAX Counter64
	MAX-ACCESS read-only
	STATUS current
	DESCRIPTION
		"The number of opt bytes DEDUPLICATION compression for IN towards LAN"
	::= { ltmIsessionProfileStatEntry 29 }

ltmIsessionProfileStatDedupInBytesRaw OBJECT-TYPE
	SYNTAX Counter64
	MAX-ACCESS read-only
	STATUS current
	DESCRIPTION
		"The number of raw bytes DEDUPLICATION compression for IN towards LAN"
	::= { ltmIsessionProfileStatEntry 30 }

ltmIsessionProfileStatDedupOutUses OBJECT-TYPE
	SYNTAX Counter64
	MAX-ACCESS read-only
	STATUS current
	DESCRIPTION
		"The number of uses DEDUPLICATION compression for OUT towards WAN"
	::= { ltmIsessionProfileStatEntry 31 }

ltmIsessionProfileStatDedupOutErrors OBJECT-TYPE
	SYNTAX Counter64
	MAX-ACCESS read-only
	STATUS current
	DESCRIPTION
		"The number of errors in use DEDUPLICATION compression for OUT towards WAN"
	::= { ltmIsessionProfileStatEntry 32 }

ltmIsessionProfileStatDedupOutBytesOpt OBJECT-TYPE
	SYNTAX Counter64
	MAX-ACCESS read-only
	STATUS current
	DESCRIPTION
		"The number of opt bytes DEDUPLICATION compression for OUT towards WAN"
	::= { ltmIsessionProfileStatEntry 33 }

ltmIsessionProfileStatDedupOutBytesRaw OBJECT-TYPE
	SYNTAX Counter64
	MAX-ACCESS read-only
	STATUS current
	DESCRIPTION
		"The number of raw bytes DEDUPLICATION compression for OUT towards WAN"
	::= { ltmIsessionProfileStatEntry 34 }

ltmIsessionProfileStatDedupInHits OBJECT-TYPE
	SYNTAX Counter64
	MAX-ACCESS read-only
	STATUS current
	DESCRIPTION
		"The number of deduplication hits for IN towards LAN"
	::= { ltmIsessionProfileStatEntry 35 }

ltmIsessionProfileStatDedupInHitBytes OBJECT-TYPE
	SYNTAX Counter64
	MAX-ACCESS read-only
	STATUS current
	DESCRIPTION
		"The number of deduplication hit bytes for IN towards LAN"
	::= { ltmIsessionProfileStatEntry 36 }

ltmIsessionProfileStatDedupInHitHistBucket1k OBJECT-TYPE
	SYNTAX Counter64
	MAX-ACCESS read-only
	STATUS current
	DESCRIPTION
		"The number of deduplication hits with size less than 1k bytes for IN towards LAN"
	::= { ltmIsessionProfileStatEntry 37 }

ltmIsessionProfileStatDedupInHitHistBucket2k OBJECT-TYPE
	SYNTAX Counter64
	MAX-ACCESS read-only
	STATUS current
	DESCRIPTION
		"The number of deduplication hits with size between 1k and 2k bytes for IN towards LAN"
	::= { ltmIsessionProfileStatEntry 38 }

ltmIsessionProfileStatDedupInHitHistBucket4k OBJECT-TYPE
	SYNTAX Counter64
	MAX-ACCESS read-only
	STATUS current
	DESCRIPTION
		"The number of deduplication hits with size between 2k and 4k bytes for IN towards LAN"
	::= { ltmIsessionProfileStatEntry 39 }

ltmIsessionProfileStatDedupInHitHistBucket8k OBJECT-TYPE
	SYNTAX Counter64
	MAX-ACCESS read-only
	STATUS current
	DESCRIPTION
		"The number of deduplication hits with size between 4k and 8k bytes for IN towards LAN"
	::= { ltmIsessionProfileStatEntry 40 }

ltmIsessionProfileStatDedupInHitHistBucket16k OBJECT-TYPE
	SYNTAX Counter64
	MAX-ACCESS read-only
	STATUS current
	DESCRIPTION
		"The number of deduplication hits with size between 8k and 16k bytes for IN towards LAN"
	::= { ltmIsessionProfileStatEntry 41 }

ltmIsessionProfileStatDedupInHitHistBucket32k OBJECT-TYPE
	SYNTAX Counter64
	MAX-ACCESS read-only
	STATUS current
	DESCRIPTION
		"The number of deduplication hits with size between 16k and 32k bytes for IN towards LAN"
	::= { ltmIsessionProfileStatEntry 42 }

ltmIsessionProfileStatDedupInHitHistBucket64k OBJECT-TYPE
	SYNTAX Counter64
	MAX-ACCESS read-only
	STATUS current
	DESCRIPTION
		"The number of deduplication hits with size between 32k and 64k bytes for IN towards LAN"
	::= { ltmIsessionProfileStatEntry 43 }

ltmIsessionProfileStatDedupInHitHistBucket128k OBJECT-TYPE
	SYNTAX Counter64
	MAX-ACCESS read-only
	STATUS current
	DESCRIPTION
		"The number of deduplication hits with size between 64k and 128k bytes for IN towards LAN"
	::= { ltmIsessionProfileStatEntry 44 }

ltmIsessionProfileStatDedupInHitHistBucket256k OBJECT-TYPE
	SYNTAX Counter64
	MAX-ACCESS read-only
	STATUS current
	DESCRIPTION
		"The number of deduplication hits with size between 128k and 256k bytes for IN towards LAN"
	::= { ltmIsessionProfileStatEntry 45 }

ltmIsessionProfileStatDedupInHitHistBucket512k OBJECT-TYPE
	SYNTAX Counter64
	MAX-ACCESS read-only
	STATUS current
	DESCRIPTION
		"The number of deduplication hits with size between 256k and 512k bytes for IN towards LAN"
	::= { ltmIsessionProfileStatEntry 46 }

ltmIsessionProfileStatDedupInHitHistBucket1m OBJECT-TYPE
	SYNTAX Counter64
	MAX-ACCESS read-only
	STATUS current
	DESCRIPTION
		"The number of deduplication hits with size between 512k and 1m bytes for IN towards LAN"
	::= { ltmIsessionProfileStatEntry 47 }

ltmIsessionProfileStatDedupInHitHistBucketLarge OBJECT-TYPE
	SYNTAX Counter64
	MAX-ACCESS read-only
	STATUS current
	DESCRIPTION
		"The number of deduplication hits with size more than 1m bytes for IN towards LAN"
	::= { ltmIsessionProfileStatEntry 48 }

ltmIsessionProfileStatDedupInMisses OBJECT-TYPE
	SYNTAX Counter64
	MAX-ACCESS read-only
	STATUS current
	DESCRIPTION
		"The number of deduplication misses for IN towards LAN"
	::= { ltmIsessionProfileStatEntry 49 }

ltmIsessionProfileStatDedupInMissBytes OBJECT-TYPE
	SYNTAX Counter64
	MAX-ACCESS read-only
	STATUS current
	DESCRIPTION
		"The number of deduplication misses bytes for IN towards LAN"
	::= { ltmIsessionProfileStatEntry 50 }

ltmIsessionProfileStatDedupInMissHistBucket1k OBJECT-TYPE
	SYNTAX Counter64
	MAX-ACCESS read-only
	STATUS current
	DESCRIPTION
		"The number of deduplication misses with size less than 1k bytes for IN towards LAN"
	::= { ltmIsessionProfileStatEntry 51 }

ltmIsessionProfileStatDedupInMissHistBucket2k OBJECT-TYPE
	SYNTAX Counter64
	MAX-ACCESS read-only
	STATUS current
	DESCRIPTION
		"The number of deduplication misses with size between 1k and 2k bytes for IN towards LAN"
	::= { ltmIsessionProfileStatEntry 52 }

ltmIsessionProfileStatDedupInMissHistBucket4k OBJECT-TYPE
	SYNTAX Counter64
	MAX-ACCESS read-only
	STATUS current
	DESCRIPTION
		"The number of deduplication misses with size between 2k and 4k bytes for IN towards LAN"
	::= { ltmIsessionProfileStatEntry 53 }

ltmIsessionProfileStatDedupInMissHistBucket8k OBJECT-TYPE
	SYNTAX Counter64
	MAX-ACCESS read-only
	STATUS current
	DESCRIPTION
		"The number of deduplication misses with size between 4k and 8k bytes for IN towards LAN"
	::= { ltmIsessionProfileStatEntry 54 }

ltmIsessionProfileStatDedupInMissHistBucket16k OBJECT-TYPE
	SYNTAX Counter64
	MAX-ACCESS read-only
	STATUS current
	DESCRIPTION
		"The number of deduplication misses with size between 8k and 16k bytes for IN towards LAN"
	::= { ltmIsessionProfileStatEntry 55 }

ltmIsessionProfileStatDedupInMissHistBucket32k OBJECT-TYPE
	SYNTAX Counter64
	MAX-ACCESS read-only
	STATUS current
	DESCRIPTION
		"The number of deduplication misses with size between 16k and 32k bytes for IN towards LAN"
	::= { ltmIsessionProfileStatEntry 56 }

ltmIsessionProfileStatDedupInMissHistBucket64k OBJECT-TYPE
	SYNTAX Counter64
	MAX-ACCESS read-only
	STATUS current
	DESCRIPTION
		"The number of deduplication misses with size between 32k and 64k bytes for IN towards LAN"
	::= { ltmIsessionProfileStatEntry 57 }

ltmIsessionProfileStatDedupInMissHistBucket128k OBJECT-TYPE
	SYNTAX Counter64
	MAX-ACCESS read-only
	STATUS current
	DESCRIPTION
		"The number of deduplication misses with size between 64k and 128k bytes for IN towards LAN"
	::= { ltmIsessionProfileStatEntry 58 }

ltmIsessionProfileStatDedupInMissHistBucket256k OBJECT-TYPE
	SYNTAX Counter64
	MAX-ACCESS read-only
	STATUS current
	DESCRIPTION
		"The number of deduplication misses with size between 128k and 256k bytes for IN towards LAN"
	::= { ltmIsessionProfileStatEntry 59 }

ltmIsessionProfileStatDedupInMissHistBucket512k OBJECT-TYPE
	SYNTAX Counter64
	MAX-ACCESS read-only
	STATUS current
	DESCRIPTION
		"The number of deduplication misses with size between 256k and 512k bytes for IN towards LAN"
	::= { ltmIsessionProfileStatEntry 60 }

ltmIsessionProfileStatDedupInMissHistBucket1m OBJECT-TYPE
	SYNTAX Counter64
	MAX-ACCESS read-only
	STATUS current
	DESCRIPTION
		"The number of deduplication misses with size between 512k and 1m bytes for IN towards LAN"
	::= { ltmIsessionProfileStatEntry 61 }

ltmIsessionProfileStatDedupInMissHistBucketLarge OBJECT-TYPE
	SYNTAX Counter64
	MAX-ACCESS read-only
	STATUS current
	DESCRIPTION
		"The number of deduplication misses with size more than 1m bytes for IN towards LAN"
	::= { ltmIsessionProfileStatEntry 62 }

ltmIsessionProfileStatDedupOutHits OBJECT-TYPE
	SYNTAX Counter64
	MAX-ACCESS read-only
	STATUS current
	DESCRIPTION
		"The number of deduplication hits for OUT towards WAN"
	::= { ltmIsessionProfileStatEntry 63 }

ltmIsessionProfileStatDedupOutHitBytes OBJECT-TYPE
	SYNTAX Counter64
	MAX-ACCESS read-only
	STATUS current
	DESCRIPTION
		"The number of deduplication hit bytes for OUT towards WAN"
	::= { ltmIsessionProfileStatEntry 64 }

ltmIsessionProfileStatDedupOutHitHistBucket1k OBJECT-TYPE
	SYNTAX Counter64
	MAX-ACCESS read-only
	STATUS current
	DESCRIPTION
		"The number of deduplication hits with size less than 1k bytes for OUT towards WAN"
	::= { ltmIsessionProfileStatEntry 65 }

ltmIsessionProfileStatDedupOutHitHistBucket2k OBJECT-TYPE
	SYNTAX Counter64
	MAX-ACCESS read-only
	STATUS current
	DESCRIPTION
		"The number of deduplication hits with size between 1k and 2k bytes for OUT towards WAN"
	::= { ltmIsessionProfileStatEntry 66 }

ltmIsessionProfileStatDedupOutHitHistBucket4k OBJECT-TYPE
	SYNTAX Counter64
	MAX-ACCESS read-only
	STATUS current
	DESCRIPTION
		"The number of deduplication hits with size between 2k and 4k bytes for OUT towards WAN"
	::= { ltmIsessionProfileStatEntry 67 }

ltmIsessionProfileStatDedupOutHitHistBucket8k OBJECT-TYPE
	SYNTAX Counter64
	MAX-ACCESS read-only
	STATUS current
	DESCRIPTION
		"The number of deduplication hits with size between 4k and 8k bytes for OUT towards WAN"
	::= { ltmIsessionProfileStatEntry 68 }

ltmIsessionProfileStatDedupOutHitHistBucket16k OBJECT-TYPE
	SYNTAX Counter64
	MAX-ACCESS read-only
	STATUS current
	DESCRIPTION
		"The number of deduplication hits with size between 8k and 16k bytes for OUT towards WAN"
	::= { ltmIsessionProfileStatEntry 69 }

ltmIsessionProfileStatDedupOutHitHistBucket32k OBJECT-TYPE
	SYNTAX Counter64
	MAX-ACCESS read-only
	STATUS current
	DESCRIPTION
		"The number of deduplication hits with size between 16k and 32k bytes for OUT towards WAN"
	::= { ltmIsessionProfileStatEntry 70 }

ltmIsessionProfileStatDedupOutHitHistBucket64k OBJECT-TYPE
	SYNTAX Counter64
	MAX-ACCESS read-only
	STATUS current
	DESCRIPTION
		"The number of deduplication hits with size between 32k and 64k bytes for OUT towards WAN"
	::= { ltmIsessionProfileStatEntry 71 }

ltmIsessionProfileStatDedupOutHitHistBucket128k OBJECT-TYPE
	SYNTAX Counter64
	MAX-ACCESS read-only
	STATUS current
	DESCRIPTION
		"The number of deduplication hits with size between 64k and 128k bytes for OUT towards WAN"
	::= { ltmIsessionProfileStatEntry 72 }

ltmIsessionProfileStatDedupOutHitHistBucket256k OBJECT-TYPE
	SYNTAX Counter64
	MAX-ACCESS read-only
	STATUS current
	DESCRIPTION
		"The number of deduplication hits with size between 128k and 256k bytes for OUT towards WAN"
	::= { ltmIsessionProfileStatEntry 73 }

ltmIsessionProfileStatDedupOutHitHistBucket512k OBJECT-TYPE
	SYNTAX Counter64
	MAX-ACCESS read-only
	STATUS current
	DESCRIPTION
		"The number of deduplication hits with size between 256k and 512k bytes for OUT towards WAN"
	::= { ltmIsessionProfileStatEntry 74 }

ltmIsessionProfileStatDedupOutHitHistBucket1m OBJECT-TYPE
	SYNTAX Counter64
	MAX-ACCESS read-only
	STATUS current
	DESCRIPTION
		"The number of deduplication hits with size between 512k and 1m bytes for OUT towards WAN"
	::= { ltmIsessionProfileStatEntry 75 }

ltmIsessionProfileStatDedupOutHitHistBucketLarge OBJECT-TYPE
	SYNTAX Counter64
	MAX-ACCESS read-only
	STATUS current
	DESCRIPTION
		"The number of deduplication hits with size more than 1m bytes for OUT towards WAN"
	::= { ltmIsessionProfileStatEntry 76 }

ltmIsessionProfileStatDedupOutMisses OBJECT-TYPE
	SYNTAX Counter64
	MAX-ACCESS read-only
	STATUS current
	DESCRIPTION
		"The number of deduplication misses for OUT towards WAN"
	::= { ltmIsessionProfileStatEntry 77 }

ltmIsessionProfileStatDedupOutMissBytes OBJECT-TYPE
	SYNTAX Counter64
	MAX-ACCESS read-only
	STATUS current
	DESCRIPTION
		"The number of deduplication misses bytes for OUT towards WAN"
	::= { ltmIsessionProfileStatEntry 78 }

ltmIsessionProfileStatDedupOutMissHistBucket1k OBJECT-TYPE
	SYNTAX Counter64
	MAX-ACCESS read-only
	STATUS current
	DESCRIPTION
		"The number of deduplication misses with size less than 1k bytes for OUT towards WAN"
	::= { ltmIsessionProfileStatEntry 79 }

ltmIsessionProfileStatDedupOutMissHistBucket2k OBJECT-TYPE
	SYNTAX Counter64
	MAX-ACCESS read-only
	STATUS current
	DESCRIPTION
		"The number of deduplication misses with size between 1k and 2k bytes for OUT towards WAN"
	::= { ltmIsessionProfileStatEntry 80 }

ltmIsessionProfileStatDedupOutMissHistBucket4k OBJECT-TYPE
	SYNTAX Counter64
	MAX-ACCESS read-only
	STATUS current
	DESCRIPTION
		"The number of deduplication misses with size between 2k and 4k bytes for OUT towards WAN"
	::= { ltmIsessionProfileStatEntry 81 }

ltmIsessionProfileStatDedupOutMissHistBucket8k OBJECT-TYPE
	SYNTAX Counter64
	MAX-ACCESS read-only
	STATUS current
	DESCRIPTION
		"The number of deduplication misses with size between 4k and 8k bytes for OUT towards WAN"
	::= { ltmIsessionProfileStatEntry 82 }

ltmIsessionProfileStatDedupOutMissHistBucket16k OBJECT-TYPE
	SYNTAX Counter64
	MAX-ACCESS read-only
	STATUS current
	DESCRIPTION
		"The number of deduplication misses with size between 8k and 16k bytes for OUT towards WAN"
	::= { ltmIsessionProfileStatEntry 83 }

ltmIsessionProfileStatDedupOutMissHistBucket32k OBJECT-TYPE
	SYNTAX Counter64
	MAX-ACCESS read-only
	STATUS current
	DESCRIPTION
		"The number of deduplication misses with size between 16k and 32k bytes for OUT towards WAN"
	::= { ltmIsessionProfileStatEntry 84 }

ltmIsessionProfileStatDedupOutMissHistBucket64k OBJECT-TYPE
	SYNTAX Counter64
	MAX-ACCESS read-only
	STATUS current
	DESCRIPTION
		"The number of deduplication misses with size between 32k and 64k bytes for OUT towards WAN"
	::= { ltmIsessionProfileStatEntry 85 }

ltmIsessionProfileStatDedupOutMissHistBucket128k OBJECT-TYPE
	SYNTAX Counter64
	MAX-ACCESS read-only
	STATUS current
	DESCRIPTION
		"The number of deduplication misses with size between 64k and 128k bytes for OUT towards WAN"
	::= { ltmIsessionProfileStatEntry 86 }

ltmIsessionProfileStatDedupOutMissHistBucket256k OBJECT-TYPE
	SYNTAX Counter64
	MAX-ACCESS read-only
	STATUS current
	DESCRIPTION
		"The number of deduplication misses with size between 128k and 256k bytes for OUT towards WAN"
	::= { ltmIsessionProfileStatEntry 87 }

ltmIsessionProfileStatDedupOutMissHistBucket512k OBJECT-TYPE
	SYNTAX Counter64
	MAX-ACCESS read-only
	STATUS current
	DESCRIPTION
		"The number of deduplication misses with size between 256k and 512k bytes for OUT towards WAN"
	::= { ltmIsessionProfileStatEntry 88 }

ltmIsessionProfileStatDedupOutMissHistBucket1m OBJECT-TYPE
	SYNTAX Counter64
	MAX-ACCESS read-only
	STATUS current
	DESCRIPTION
		"The number of deduplication misses with size between 512k and 1m bytes for OUT towards WAN"
	::= { ltmIsessionProfileStatEntry 89 }

ltmIsessionProfileStatDedupOutMissHistBucketLarge OBJECT-TYPE
	SYNTAX Counter64
	MAX-ACCESS read-only
	STATUS current
	DESCRIPTION
		"The number of deduplication misses with size more than 1m bytes for OUT towards WAN"
	::= { ltmIsessionProfileStatEntry 90 }

ltmIsessionProfileStatOutgoingConnsIdleCur OBJECT-TYPE
	SYNTAX Gauge
	MAX-ACCESS read-only
	STATUS current
	DESCRIPTION
		"The current number of outgoing idle connections"
	::= { ltmIsessionProfileStatEntry 91 }

ltmIsessionProfileStatOutgoingConnsIdleMax OBJECT-TYPE
	SYNTAX Counter64
	MAX-ACCESS read-only
	STATUS current
	DESCRIPTION
		"The maximum number of outgoing idle connections"
	::= { ltmIsessionProfileStatEntry 92 }

ltmIsessionProfileStatOutgoingConnsIdleTot OBJECT-TYPE
	SYNTAX Counter64
	MAX-ACCESS read-only
	STATUS current
	DESCRIPTION
		"The total number of outgoing idle connections"
	::= { ltmIsessionProfileStatEntry 93 }

ltmIsessionProfileStatOutgoingConnsActiveCur OBJECT-TYPE
	SYNTAX Gauge
	MAX-ACCESS read-only
	STATUS current
	DESCRIPTION
		"The current number of outgoing active connections"
	::= { ltmIsessionProfileStatEntry 94 }

ltmIsessionProfileStatOutgoingConnsActiveMax OBJECT-TYPE
	SYNTAX Counter64
	MAX-ACCESS read-only
	STATUS current
	DESCRIPTION
		"The maximum number of outgoing active connections"
	::= { ltmIsessionProfileStatEntry 95 }

ltmIsessionProfileStatOutgoingConnsActiveTot OBJECT-TYPE
	SYNTAX Counter64
	MAX-ACCESS read-only
	STATUS current
	DESCRIPTION
		"The total number of outgoing active connections"
	::= { ltmIsessionProfileStatEntry 96 }

ltmIsessionProfileStatOutgoingConnsErrors OBJECT-TYPE
	SYNTAX Counter64
	MAX-ACCESS read-only
	STATUS current
	DESCRIPTION
		"The number of outgoing connection errors"
	::= { ltmIsessionProfileStatEntry 97 }

ltmIsessionProfileStatOutgoingConnsPassthruTot OBJECT-TYPE
	SYNTAX Counter64
	MAX-ACCESS read-only
	STATUS current
	DESCRIPTION
		"The number of outgoing passthrough connections"
	::= { ltmIsessionProfileStatEntry 98 }

ltmIsessionProfileStatIncomingConnsActiveCur OBJECT-TYPE
	SYNTAX Gauge
	MAX-ACCESS read-only
	STATUS current
	DESCRIPTION
		"The current number of incoming active connections"
	::= { ltmIsessionProfileStatEntry 99 }

ltmIsessionProfileStatIncomingConnsActiveMax OBJECT-TYPE
	SYNTAX Counter64
	MAX-ACCESS read-only
	STATUS current
	DESCRIPTION
		"The maximum number of incoming active connections"
	::= { ltmIsessionProfileStatEntry 100 }

ltmIsessionProfileStatIncomingConnsActiveTot OBJECT-TYPE
	SYNTAX Counter64
	MAX-ACCESS read-only
	STATUS current
	DESCRIPTION
		"The total number of incoming active connections"
	::= { ltmIsessionProfileStatEntry 101 }

ltmIsessionProfileStatIncomingConnsErrors OBJECT-TYPE
	SYNTAX Counter64
	MAX-ACCESS read-only
	STATUS current
	DESCRIPTION
		"The number of incoming connection errors"
	::= { ltmIsessionProfileStatEntry 102 }

ltmIsessionProfileStatBzip2InUses OBJECT-TYPE
	SYNTAX Counter64
	MAX-ACCESS read-only
	STATUS current
	DESCRIPTION
		"The number of uses BZIP2 compression for IN towards LAN"
	::= { ltmIsessionProfileStatEntry 103 }

ltmIsessionProfileStatBzip2InErrors OBJECT-TYPE
	SYNTAX Counter64
	MAX-ACCESS read-only
	STATUS current
	DESCRIPTION
		"The number of errors in use BZIP2 compression for IN towards LAN"
	::= { ltmIsessionProfileStatEntry 104 }

ltmIsessionProfileStatBzip2InBytesOpt OBJECT-TYPE
	SYNTAX Counter64
	MAX-ACCESS read-only
	STATUS current
	DESCRIPTION
		"The number of opt bytes BZIP2 compression for IN towards LAN"
	::= { ltmIsessionProfileStatEntry 105 }

ltmIsessionProfileStatBzip2InBytesRaw OBJECT-TYPE
	SYNTAX Counter64
	MAX-ACCESS read-only
	STATUS current
	DESCRIPTION
		"The number of raw bytes BZIP2 compression for IN towards LAN"
	::= { ltmIsessionProfileStatEntry 106 }

ltmIsessionProfileStatBzip2OutUses OBJECT-TYPE
	SYNTAX Counter64
	MAX-ACCESS read-only
	STATUS current
	DESCRIPTION
		"The number of uses BZIP2 compression for OUT towards WAN"
	::= { ltmIsessionProfileStatEntry 107 }

ltmIsessionProfileStatBzip2OutErrors OBJECT-TYPE
	SYNTAX Counter64
	MAX-ACCESS read-only
	STATUS current
	DESCRIPTION
		"The number of errors in use BZIP2 compression for OUT towards WAN"
	::= { ltmIsessionProfileStatEntry 108 }

ltmIsessionProfileStatBzip2OutBytesOpt OBJECT-TYPE
	SYNTAX Counter64
	MAX-ACCESS read-only
	STATUS current
	DESCRIPTION
		"The number of opt bytes BZIP2 compression for OUT towards WAN"
	::= { ltmIsessionProfileStatEntry 109 }

ltmIsessionProfileStatBzip2OutBytesRaw OBJECT-TYPE
	SYNTAX Counter64
	MAX-ACCESS read-only
	STATUS current
	DESCRIPTION
		"The number of raw bytes BZIP2 compression for OUT towards WAN"
	::= { ltmIsessionProfileStatEntry 110 }

--==================================================================
-- Profile_xml_xpath_queries
--==================================================================
ltmXmlProfileXpathQueriesNumber OBJECT-TYPE
	SYNTAX INTEGER
	MAX-ACCESS read-only
	STATUS current
	DESCRIPTION
		"The number of ltmXmlProfileXpathQueries entries in the table."
	::= { ltmXmlProfileXpathQueries 1 }

ltmXmlProfileXpathQueriesTable OBJECT-TYPE
	SYNTAX SEQUENCE OF LtmXmlProfileXpathQueriesEntry
	MAX-ACCESS not-accessible
	STATUS current
	DESCRIPTION
		"A table containing information of XPath queries in xml profiles."
	::= { ltmXmlProfileXpathQueries 2 }

ltmXmlProfileXpathQueriesEntry OBJECT-TYPE
	SYNTAX  LtmXmlProfileXpathQueriesEntry
	MAX-ACCESS not-accessible
	STATUS current
	DESCRIPTION
		"Columns in the ltmXmlProfileXpathQueries Table"
	INDEX {
		ltmXmlProfileXpathQueriesName,
		ltmXmlProfileXpathQueriesIndex
	}
	::= { ltmXmlProfileXpathQueriesTable 1 }

LtmXmlProfileXpathQueriesEntry ::=
	SEQUENCE {
        	ltmXmlProfileXpathQueriesName                             LongDisplayString,
        	ltmXmlProfileXpathQueriesIndex                            INTEGER,
        	ltmXmlProfileXpathQueriesString                           LongDisplayString
	}

ltmXmlProfileXpathQueriesName OBJECT-TYPE
	SYNTAX LongDisplayString
	MAX-ACCESS read-only
	STATUS current
	DESCRIPTION
		"The name of an xml profile."
	::= { ltmXmlProfileXpathQueriesEntry 1 }

ltmXmlProfileXpathQueriesIndex OBJECT-TYPE
	SYNTAX INTEGER(0..2147483647)
	MAX-ACCESS read-only
	STATUS current
	DESCRIPTION
		"The index of XPath queries for the specified xml profile."
	::= { ltmXmlProfileXpathQueriesEntry 2 }

ltmXmlProfileXpathQueriesString OBJECT-TYPE
	SYNTAX LongDisplayString
	MAX-ACCESS read-only
	STATUS current
	DESCRIPTION
		"The XPath query for the specified profile."
	::= { ltmXmlProfileXpathQueriesEntry 3 }

--==================================================================
-- Profile_xml_namespace_mappings
--==================================================================
ltmXmlProfileNamespaceMappingsNumber OBJECT-TYPE
	SYNTAX INTEGER
	MAX-ACCESS read-only
	STATUS current
	DESCRIPTION
		"The number of ltmXmlProfileNamespaceMappings entries in the table."
	::= { ltmXmlProfileNamespaceMappings 1 }

ltmXmlProfileNamespaceMappingsTable OBJECT-TYPE
	SYNTAX SEQUENCE OF LtmXmlProfileNamespaceMappingsEntry
	MAX-ACCESS not-accessible
	STATUS current
	DESCRIPTION
		"A table containing information of namespace mappings in xml profiles."
	::= { ltmXmlProfileNamespaceMappings 2 }

ltmXmlProfileNamespaceMappingsEntry OBJECT-TYPE
	SYNTAX  LtmXmlProfileNamespaceMappingsEntry
	MAX-ACCESS not-accessible
	STATUS current
	DESCRIPTION
		"Columns in the ltmXmlProfileNamespaceMappings Table"
	INDEX {
		ltmXmlProfileNamespaceMappingsName,
		ltmXmlProfileNamespaceMappingsIndex
	}
	::= { ltmXmlProfileNamespaceMappingsTable 1 }

LtmXmlProfileNamespaceMappingsEntry ::=
	SEQUENCE {
        	ltmXmlProfileNamespaceMappingsName                        LongDisplayString,
        	ltmXmlProfileNamespaceMappingsIndex                       INTEGER,
        	ltmXmlProfileNamespaceMappingsMappingPrefix               LongDisplayString,
        	ltmXmlProfileNamespaceMappingsMappingNamespace            LongDisplayString
	}

ltmXmlProfileNamespaceMappingsName OBJECT-TYPE
	SYNTAX LongDisplayString
	MAX-ACCESS read-only
	STATUS current
	DESCRIPTION
		"The name of an xml profile."
	::= { ltmXmlProfileNamespaceMappingsEntry 1 }

ltmXmlProfileNamespaceMappingsIndex OBJECT-TYPE
	SYNTAX INTEGER(0..2147483647)
	MAX-ACCESS read-only
	STATUS current
	DESCRIPTION
		"The index of Namespace Mappings for the specified xml profile."
	::= { ltmXmlProfileNamespaceMappingsEntry 2 }

ltmXmlProfileNamespaceMappingsMappingPrefix OBJECT-TYPE
	SYNTAX LongDisplayString
	MAX-ACCESS read-only
	STATUS current
	DESCRIPTION
		"The Namespace Mapping Prefix for the specified profile."
	::= { ltmXmlProfileNamespaceMappingsEntry 3 }

ltmXmlProfileNamespaceMappingsMappingNamespace OBJECT-TYPE
	SYNTAX LongDisplayString
	MAX-ACCESS read-only
	STATUS current
	DESCRIPTION
		"The Namespace Mapping Namespace for the specified profile."
	::= { ltmXmlProfileNamespaceMappingsEntry 4 }

--==================================================================
-- Profile_httpcompression
--==================================================================
ltmHttpCompressionProfileNumber OBJECT-TYPE
	SYNTAX INTEGER
	MAX-ACCESS read-only
	STATUS current
	DESCRIPTION
		"The number of ltmHttpCompressionProfile entries in the table."
	::= { ltmHttpCompressionProfile 1 }

ltmHttpCompressionProfileTable OBJECT-TYPE
	SYNTAX SEQUENCE OF LtmHttpCompressionProfileEntry
	MAX-ACCESS not-accessible
	STATUS current
	DESCRIPTION
		"A table containing information of HTTP Compression profiles."
	::= { ltmHttpCompressionProfile 2 }

ltmHttpCompressionProfileEntry OBJECT-TYPE
	SYNTAX  LtmHttpCompressionProfileEntry
	MAX-ACCESS not-accessible
	STATUS current
	DESCRIPTION
		"Columns in the ltmHttpCompressionProfile Table"
	INDEX {
		ltmHttpCompressionProfileName
	}
	::= { ltmHttpCompressionProfileTable 1 }

LtmHttpCompressionProfileEntry ::=
	SEQUENCE {
        	ltmHttpCompressionProfileName                             LongDisplayString,
        	ltmHttpCompressionProfileConfigSource                     INTEGER,
        	ltmHttpCompressionProfileDefaultName                      LongDisplayString,
        	ltmHttpCompressionProfileSelective                        INTEGER,
        	ltmHttpCompressionProfileMinSize                          Gauge,
        	ltmHttpCompressionProfileBufferSize                       Gauge,
        	ltmHttpCompressionProfileVaryHeader                       INTEGER,
        	ltmHttpCompressionProfileAllowHttp10                      INTEGER,
        	ltmHttpCompressionProfileGzipMemlevel                     Gauge,
        	ltmHttpCompressionProfileGzipWindowsize                   Gauge,
        	ltmHttpCompressionProfileGzipLevel                        Gauge,
        	ltmHttpCompressionProfileKeepAcceptEncoding               INTEGER,
        	ltmHttpCompressionProfileBrowserWorkarounds               INTEGER,
        	ltmHttpCompressionProfileCpusaver                         INTEGER,
        	ltmHttpCompressionProfileCpusaverHigh                     Gauge,
        	ltmHttpCompressionProfileCpusaverLow                      Gauge,
        	ltmHttpCompressionProfilePreferredMethod                  INTEGER
	}

ltmHttpCompressionProfileName OBJECT-TYPE
	SYNTAX LongDisplayString
	MAX-ACCESS read-only
	STATUS current
	DESCRIPTION
		"The name of a HTTP compression profile."
	::= { ltmHttpCompressionProfileEntry 1 }

ltmHttpCompressionProfileConfigSource OBJECT-TYPE
	SYNTAX INTEGER {
		usercfg(0),
		basecfg(1)
	}
	MAX-ACCESS read-only
	STATUS current
	DESCRIPTION
		"The state that specifies whether this is a base/pre-configured profile
		or user defined profile."
	::= { ltmHttpCompressionProfileEntry 2 }

ltmHttpCompressionProfileDefaultName OBJECT-TYPE
	SYNTAX LongDisplayString
	MAX-ACCESS read-only
	STATUS current
	DESCRIPTION
		"The name of the profile from which the specified profile derives
		its attribute default values."
	::= { ltmHttpCompressionProfileEntry 3 }

ltmHttpCompressionProfileSelective OBJECT-TYPE
	SYNTAX INTEGER {
		false(0),
		true(1)
	}
	MAX-ACCESS read-only
	STATUS current
	DESCRIPTION
		"The state that specifies whether selective compression is enabled."
	::= { ltmHttpCompressionProfileEntry 4 }

ltmHttpCompressionProfileMinSize OBJECT-TYPE
	SYNTAX Gauge
	MAX-ACCESS read-only
	STATUS current
	DESCRIPTION
		"The value that specifies the minimum length of the server
		responses (in bytes) to be considered acceptable for compression."
	::= { ltmHttpCompressionProfileEntry 5 }

ltmHttpCompressionProfileBufferSize OBJECT-TYPE
	SYNTAX Gauge
	MAX-ACCESS read-only
	STATUS current
	DESCRIPTION
		"The value that specifies the maximum number of uncompressed bytes
		that the compression proxy will buffer before it decides whether or
		not to compress the server's response, in case the server's response
		headers don't specify the content length of the response."
	::= { ltmHttpCompressionProfileEntry 6 }

ltmHttpCompressionProfileVaryHeader OBJECT-TYPE
	SYNTAX INTEGER {
		false(0),
		true(1)
	}
	MAX-ACCESS read-only
	STATUS current
	DESCRIPTION
		"The state that specifies whether to insert the header
		'Vary: Accept-Encoding' in the server response for responses that
		have been compressed. If the 'Vary:' header already exists in the
		server response, then the value 'Accept-Encoding' will be appended to it."
	::= { ltmHttpCompressionProfileEntry 7 }

ltmHttpCompressionProfileAllowHttp10 OBJECT-TYPE
	SYNTAX INTEGER {
		false(0),
		true(1)
	}
	MAX-ACCESS read-only
	STATUS current
	DESCRIPTION
		"The state that specifies whether to allow compression on responses
		to HTTP 1.0 requests."
	::= { ltmHttpCompressionProfileEntry 8 }

ltmHttpCompressionProfileGzipMemlevel OBJECT-TYPE
	SYNTAX Gauge
	MAX-ACCESS read-only
	STATUS current
	DESCRIPTION
		"The amount of memory that the proxy will use when doing compression.
		It must be an integer no less than 1 and no greater than 9. Higher
		values produce faster compression at the expense of more memory usage.
		The default memory level will be 8."
	::= { ltmHttpCompressionProfileEntry 9 }

ltmHttpCompressionProfileGzipWindowsize OBJECT-TYPE
	SYNTAX Gauge
	MAX-ACCESS read-only
	STATUS current
	DESCRIPTION
		"The number of bits in the window size that the compression proxy
		will use when compressing the server response. It should be an integer
		no less than 8 and no greater than 15. Higher values produce better
		compression ratios at the expense of more memory usage.
		The default window size will be 15."
	::= { ltmHttpCompressionProfileEntry 10 }

ltmHttpCompressionProfileGzipLevel OBJECT-TYPE
	SYNTAX Gauge
	MAX-ACCESS read-only
	STATUS current
	DESCRIPTION
		"The speed of compression that is applied to the response. Minimum
		value is 1, maximum is 9. The lower numbers give faster compression
		with lower ratios, and higher numbers give slower compression with
		higher ratios."
	::= { ltmHttpCompressionProfileEntry 11 }

ltmHttpCompressionProfileKeepAcceptEncoding OBJECT-TYPE
	SYNTAX INTEGER {
		false(0),
		true(1)
	}
	MAX-ACCESS read-only
	STATUS current
	DESCRIPTION
		"The state of the option to keep client-encoding header."
	::= { ltmHttpCompressionProfileEntry 12 }

ltmHttpCompressionProfileBrowserWorkarounds OBJECT-TYPE
	SYNTAX INTEGER {
		false(0),
		true(1)
	}
	MAX-ACCESS read-only
	STATUS	 deprecated
	DESCRIPTION
		"Deprecated! The option to control whether or not to disable compression for
		known browsers that cannot handle certain types of compressed
		responses properly. If it's true, compression for known browsers
		will be disabled."
	::= { ltmHttpCompressionProfileEntry 13 }

ltmHttpCompressionProfileCpusaver OBJECT-TYPE
	SYNTAX INTEGER {
		false(0),
		true(1)
	}
	MAX-ACCESS read-only
	STATUS current
	DESCRIPTION
		"The state indicating whether CPU saving mode is enable or not
		when doing compression."
	::= { ltmHttpCompressionProfileEntry 14 }

ltmHttpCompressionProfileCpusaverHigh OBJECT-TYPE
	SYNTAX Gauge
	MAX-ACCESS read-only
	STATUS current
	DESCRIPTION
		"The CPU saver high threshold. When CPU utilization exceeds this value,
		compression is switched to NULL compression."
	::= { ltmHttpCompressionProfileEntry 15 }

ltmHttpCompressionProfileCpusaverLow OBJECT-TYPE
	SYNTAX Gauge
	MAX-ACCESS read-only
	STATUS current
	DESCRIPTION
		"The CPU saver low threshold. When CPU utilization drops below
		this value, compression is switched to full throttle."
	::= { ltmHttpCompressionProfileEntry 16 }

ltmHttpCompressionProfilePreferredMethod OBJECT-TYPE
	SYNTAX INTEGER {
		deflate(0),
		gzip(1)
	}
	MAX-ACCESS read-only
	STATUS current
	DESCRIPTION
		"The option for preferred compression method."
	::= { ltmHttpCompressionProfileEntry 17 }

--==================================================================
-- Profile_httpcompression_uri_includes
--==================================================================
ltmHttpcompUriInclNumber OBJECT-TYPE
	SYNTAX INTEGER
	MAX-ACCESS read-only
	STATUS current
	DESCRIPTION
		"The number of ltmHttpCompressionProfileUriIncl entries in the table."
	::= { ltmHttpCompressionProfileUriIncl 1 }

ltmHttpcompUriInclTable OBJECT-TYPE
	SYNTAX SEQUENCE OF LtmHttpcompUriInclEntry
	MAX-ACCESS not-accessible
	STATUS current
	DESCRIPTION
		"A table containing information of regular expressions used to match
		the request URI part of the client requests during compression.
		A match must be found in at least one of the 'include' fields."
	::= { ltmHttpCompressionProfileUriIncl 2 }

ltmHttpcompUriInclEntry OBJECT-TYPE
	SYNTAX  LtmHttpcompUriInclEntry
	MAX-ACCESS not-accessible
	STATUS current
	DESCRIPTION
		"Columns in the ltmHttpcompUriIncl Table"
	INDEX {
		ltmHttpcompUriInclName,
		ltmHttpcompUriInclIndex
	}
	::= { ltmHttpcompUriInclTable 1 }

LtmHttpcompUriInclEntry ::=
	SEQUENCE {
        	ltmHttpcompUriInclName                                    LongDisplayString,
        	ltmHttpcompUriInclIndex                                   INTEGER,
        	ltmHttpcompUriInclUri                                     LongDisplayString
	}

ltmHttpcompUriInclName OBJECT-TYPE
	SYNTAX LongDisplayString
	MAX-ACCESS read-only
	STATUS current
	DESCRIPTION
		"The name of a HTTP Compression profile."
	::= { ltmHttpcompUriInclEntry 1 }

ltmHttpcompUriInclIndex OBJECT-TYPE
	SYNTAX INTEGER(0..2147483647)
	MAX-ACCESS read-only
	STATUS current
	DESCRIPTION
		"The index of the regular expression used to match the request
		URI part of the client requests during compression in
		'include' fields for the specified HTTP Compression profile."
	::= { ltmHttpcompUriInclEntry 2 }

ltmHttpcompUriInclUri OBJECT-TYPE
	SYNTAX LongDisplayString
	MAX-ACCESS read-only
	STATUS current
	DESCRIPTION
		"The regular expression used to match the request URI part
		of the client requests during compression in 'include' fields
		for the specified HTTP Compression profile."
	::= { ltmHttpcompUriInclEntry 3 }

--==================================================================
-- Profile_httpcompression_uri_excludes
--==================================================================
ltmHttpcompUriExclNumber OBJECT-TYPE
	SYNTAX INTEGER
	MAX-ACCESS read-only
	STATUS current
	DESCRIPTION
		"The number of ltmHttpCompressionProfileUriExcl entries in the table."
	::= { ltmHttpCompressionProfileUriExcl 1 }

ltmHttpcompUriExclTable OBJECT-TYPE
	SYNTAX SEQUENCE OF LtmHttpcompUriExclEntry
	MAX-ACCESS not-accessible
	STATUS current
	DESCRIPTION
		"A table containing information of regular expressions used to match
		the request URI part of the client requests during compression.
		A match must be found in at least one of the 'exclude' fields."
	::= { ltmHttpCompressionProfileUriExcl 2 }

ltmHttpcompUriExclEntry OBJECT-TYPE
	SYNTAX  LtmHttpcompUriExclEntry
	MAX-ACCESS not-accessible
	STATUS current
	DESCRIPTION
		"Columns in the ltmHttpcompUriExcl Table"
	INDEX {
		ltmHttpcompUriExclName,
		ltmHttpcompUriExclIndex
	}
	::= { ltmHttpcompUriExclTable 1 }

LtmHttpcompUriExclEntry ::=
	SEQUENCE {
        	ltmHttpcompUriExclName                                    LongDisplayString,
        	ltmHttpcompUriExclIndex                                   INTEGER,
        	ltmHttpcompUriExclUri                                     LongDisplayString
	}

ltmHttpcompUriExclName OBJECT-TYPE
	SYNTAX LongDisplayString
	MAX-ACCESS read-only
	STATUS current
	DESCRIPTION
		"The name of a HTTP Compression profile."
	::= { ltmHttpcompUriExclEntry 1 }

ltmHttpcompUriExclIndex OBJECT-TYPE
	SYNTAX INTEGER(0..2147483647)
	MAX-ACCESS read-only
	STATUS current
	DESCRIPTION
		"The index of the regular expression used to match the request
		URI part of the client requests during compression in
		'exclude' fields for the specified HTTP Compression profile."
	::= { ltmHttpcompUriExclEntry 2 }

ltmHttpcompUriExclUri OBJECT-TYPE
	SYNTAX LongDisplayString
	MAX-ACCESS read-only
	STATUS current
	DESCRIPTION
		"The regular expression used to match the request URI part
		of the client requests during compression in 'exclude' fields
		for the specified HTTP Compression profile."
	::= { ltmHttpcompUriExclEntry 3 }

--==================================================================
-- Profile_httpcompression_content_type_includes
--==================================================================
ltmHttpcompContTypeInclNumber OBJECT-TYPE
	SYNTAX INTEGER
	MAX-ACCESS read-only
	STATUS current
	DESCRIPTION
		"The number of ltmHttpCompressionProfileContTypeIncl entries in the table."
	::= { ltmHttpCompressionProfileContTypeIncl 1 }

ltmHttpcompContTypeInclTable OBJECT-TYPE
	SYNTAX SEQUENCE OF LtmHttpcompContTypeInclEntry
	MAX-ACCESS not-accessible
	STATUS current
	DESCRIPTION
		"A table containing information of regular expressions used to match
		the MIME types in the server response's 'Content-Type:' headers.
		A match must be found in at least one of the 'include' fields."
	::= { ltmHttpCompressionProfileContTypeIncl 2 }

ltmHttpcompContTypeInclEntry OBJECT-TYPE
	SYNTAX  LtmHttpcompContTypeInclEntry
	MAX-ACCESS not-accessible
	STATUS current
	DESCRIPTION
		"Columns in the ltmHttpcompContTypeIncl Table"
	INDEX {
		ltmHttpcompContTypeInclName,
		ltmHttpcompContTypeInclIndex
	}
	::= { ltmHttpcompContTypeInclTable 1 }

LtmHttpcompContTypeInclEntry ::=
	SEQUENCE {
        	ltmHttpcompContTypeInclName                               LongDisplayString,
        	ltmHttpcompContTypeInclIndex                              INTEGER,
        	ltmHttpcompContTypeInclContentType                        LongDisplayString
	}

ltmHttpcompContTypeInclName OBJECT-TYPE
	SYNTAX LongDisplayString
	MAX-ACCESS read-only
	STATUS current
	DESCRIPTION
		"The name of a HTTP Compression profile."
	::= { ltmHttpcompContTypeInclEntry 1 }

ltmHttpcompContTypeInclIndex OBJECT-TYPE
	SYNTAX INTEGER(0..2147483647)
	MAX-ACCESS read-only
	STATUS current
	DESCRIPTION
		"The index of the regular expression to match the MIME types in the
	        server response's 'Content-Type:' headers in 'include' fields for
		the specified HTTP Compression profile."
	::= { ltmHttpcompContTypeInclEntry 2 }

ltmHttpcompContTypeInclContentType OBJECT-TYPE
	SYNTAX LongDisplayString
	MAX-ACCESS read-only
	STATUS current
	DESCRIPTION
		"The regular expression used to match the MIME types in the server
		response's 'Content-Type:' headers in 'include' fields for the
		specified HTTP Compression profile."
	::= { ltmHttpcompContTypeInclEntry 3 }

--==================================================================
-- Profile_httpcompression_content_type_excludes
--==================================================================
ltmHttpcompContTypeExclNumber OBJECT-TYPE
	SYNTAX INTEGER
	MAX-ACCESS read-only
	STATUS current
	DESCRIPTION
		"The number of ltmHttpCompressionProfileContTypeExcl entries in the table."
	::= { ltmHttpCompressionProfileContTypeExcl 1 }

ltmHttpcompContTypeExclTable OBJECT-TYPE
	SYNTAX SEQUENCE OF LtmHttpcompContTypeExclEntry
	MAX-ACCESS not-accessible
	STATUS current
	DESCRIPTION
		"A table containing information of regular expressions used to match
		the MIME types in the server response's 'Content-Type:' headers.
		A match must be found in at least one of the 'exclude' fields."
	::= { ltmHttpCompressionProfileContTypeExcl 2 }

ltmHttpcompContTypeExclEntry OBJECT-TYPE
	SYNTAX  LtmHttpcompContTypeExclEntry
	MAX-ACCESS not-accessible
	STATUS current
	DESCRIPTION
		"Columns in the ltmHttpcompContTypeExcl Table"
	INDEX {
		ltmHttpcompContTypeExclName,
		ltmHttpcompContTypeExclIndex
	}
	::= { ltmHttpcompContTypeExclTable 1 }

LtmHttpcompContTypeExclEntry ::=
	SEQUENCE {
        	ltmHttpcompContTypeExclName                               LongDisplayString,
        	ltmHttpcompContTypeExclIndex                              INTEGER,
        	ltmHttpcompContTypeExclContentType                        LongDisplayString
	}

ltmHttpcompContTypeExclName OBJECT-TYPE
	SYNTAX LongDisplayString
	MAX-ACCESS read-only
	STATUS current
	DESCRIPTION
		"The name of a HTTP Compression profile."
	::= { ltmHttpcompContTypeExclEntry 1 }

ltmHttpcompContTypeExclIndex OBJECT-TYPE
	SYNTAX INTEGER(0..2147483647)
	MAX-ACCESS read-only
	STATUS current
	DESCRIPTION
		"The index of the regular expression to match the MIME types in the
	        server response's 'Content-Type:' headers in 'exclude' fields for
		the specified HTTP Compression profile."
	::= { ltmHttpcompContTypeExclEntry 2 }

ltmHttpcompContTypeExclContentType OBJECT-TYPE
	SYNTAX LongDisplayString
	MAX-ACCESS read-only
	STATUS current
	DESCRIPTION
		"The regular expression used to match the MIME types in the server
		response's 'Content-Type:' headers in 'exclude' fields for the
		specified HTTP Compression profile."
	::= { ltmHttpcompContTypeExclEntry 3 }

--==================================================================
-- Profile_httpcompression_stat
--==================================================================
ltmHttpCompressionProfileStatResetStats OBJECT-TYPE
	SYNTAX INTEGER
	MAX-ACCESS read-write
	STATUS current
	DESCRIPTION
		"The action to reset resettable statistics data in ltmHttpCompressionProfileStat.
		 Setting this value to 1 will reset statistics data.
		 Note, some statistics data may not be reset including data that are incremental counters."
	::= { ltmHttpCompressionProfileStat 1 }

ltmHttpCompressionProfileStatNumber OBJECT-TYPE
	SYNTAX INTEGER
	MAX-ACCESS read-only
	STATUS current
	DESCRIPTION
		"The number of ltmHttpCompressionProfileStat entries in the table."
	::= { ltmHttpCompressionProfileStat 2 }

ltmHttpCompressionProfileStatTable OBJECT-TYPE
	SYNTAX SEQUENCE OF LtmHttpCompressionProfileStatEntry
	MAX-ACCESS not-accessible
	STATUS current
	DESCRIPTION
		"A table containing statistic information of HTTP Compression profiles."
	::= { ltmHttpCompressionProfileStat 3 }

ltmHttpCompressionProfileStatEntry OBJECT-TYPE
	SYNTAX  LtmHttpCompressionProfileStatEntry
	MAX-ACCESS not-accessible
	STATUS current
	DESCRIPTION
		"Columns in the ltmHttpCompressionProfileStat Table"
	INDEX {
		ltmHttpCompressionProfileStatName
	}
	::= { ltmHttpCompressionProfileStatTable 1 }

LtmHttpCompressionProfileStatEntry ::=
	SEQUENCE {
        	ltmHttpCompressionProfileStatName                         LongDisplayString,
        	ltmHttpCompressionProfileStatPrecompressBytes             Counter64,
        	ltmHttpCompressionProfileStatPostcompressBytes            Counter64,
        	ltmHttpCompressionProfileStatNullCompressBytes            Counter64,
        	ltmHttpCompressionProfileStatHtmlPrecompressBytes         Counter64,
        	ltmHttpCompressionProfileStatHtmlPostcompressBytes        Counter64,
        	ltmHttpCompressionProfileStatCssPrecompressBytes          Counter64,
        	ltmHttpCompressionProfileStatCssPostcompressBytes         Counter64,
        	ltmHttpCompressionProfileStatJsPrecompressBytes           Counter64,
        	ltmHttpCompressionProfileStatJsPostcompressBytes          Counter64,
        	ltmHttpCompressionProfileStatXmlPrecompressBytes          Counter64,
        	ltmHttpCompressionProfileStatXmlPostcompressBytes         Counter64,
        	ltmHttpCompressionProfileStatSgmlPrecompressBytes         Counter64,
        	ltmHttpCompressionProfileStatSgmlPostcompressBytes        Counter64,
        	ltmHttpCompressionProfileStatPlainPrecompressBytes        Counter64,
        	ltmHttpCompressionProfileStatPlainPostcompressBytes       Counter64,
        	ltmHttpCompressionProfileStatOctetPrecompressBytes        Counter64,
        	ltmHttpCompressionProfileStatOctetPostcompressBytes       Counter64,
        	ltmHttpCompressionProfileStatImagePrecompressBytes        Counter64,
        	ltmHttpCompressionProfileStatImagePostcompressBytes       Counter64,
        	ltmHttpCompressionProfileStatVideoPrecompressBytes        Counter64,
        	ltmHttpCompressionProfileStatVideoPostcompressBytes       Counter64,
        	ltmHttpCompressionProfileStatAudioPrecompressBytes        Counter64,
        	ltmHttpCompressionProfileStatAudioPostcompressBytes       Counter64,
        	ltmHttpCompressionProfileStatOtherPrecompressBytes        Counter64,
        	ltmHttpCompressionProfileStatOtherPostcompressBytes       Counter64
	}

ltmHttpCompressionProfileStatName OBJECT-TYPE
	SYNTAX LongDisplayString
	MAX-ACCESS read-only
	STATUS current
	DESCRIPTION
		"The name of a HTTP Compression profile."
	::= { ltmHttpCompressionProfileStatEntry 1 }

ltmHttpCompressionProfileStatPrecompressBytes OBJECT-TYPE
	SYNTAX Counter64
	MAX-ACCESS read-only
	STATUS current
	DESCRIPTION
		"The number of response bytes before compression has taken place."
	::= { ltmHttpCompressionProfileStatEntry 2 }

ltmHttpCompressionProfileStatPostcompressBytes OBJECT-TYPE
	SYNTAX Counter64
	MAX-ACCESS read-only
	STATUS current
	DESCRIPTION
		"The number of response bytes after compression has taken place."
	::= { ltmHttpCompressionProfileStatEntry 3 }

ltmHttpCompressionProfileStatNullCompressBytes OBJECT-TYPE
	SYNTAX Counter64
	MAX-ACCESS read-only
	STATUS current
	DESCRIPTION
		"The number of bytes subjected to NULL compression (for license enforcement)."
	::= { ltmHttpCompressionProfileStatEntry 4 }

ltmHttpCompressionProfileStatHtmlPrecompressBytes OBJECT-TYPE
	SYNTAX Counter64
	MAX-ACCESS read-only
	STATUS current
	DESCRIPTION
		"The number of pre-compressed bytes for the MIME-Types: HTML."
	::= { ltmHttpCompressionProfileStatEntry 5 }

ltmHttpCompressionProfileStatHtmlPostcompressBytes OBJECT-TYPE
	SYNTAX Counter64
	MAX-ACCESS read-only
	STATUS current
	DESCRIPTION
		"The number of post-compressed bytes for the MIME-Types: HTML."
	::= { ltmHttpCompressionProfileStatEntry 6 }

ltmHttpCompressionProfileStatCssPrecompressBytes OBJECT-TYPE
	SYNTAX Counter64
	MAX-ACCESS read-only
	STATUS current
	DESCRIPTION
		"The number of pre-compressed bytes for the MIME-Types: CSS."
	::= { ltmHttpCompressionProfileStatEntry 7 }

ltmHttpCompressionProfileStatCssPostcompressBytes OBJECT-TYPE
	SYNTAX Counter64
	MAX-ACCESS read-only
	STATUS current
	DESCRIPTION
		"The number of post-compressed bytes for the MIME-Types: CSS."
	::= { ltmHttpCompressionProfileStatEntry 8 }

ltmHttpCompressionProfileStatJsPrecompressBytes OBJECT-TYPE
	SYNTAX Counter64
	MAX-ACCESS read-only
	STATUS current
	DESCRIPTION
		"The number of pre-compressed bytes for the MIME-Types: Javascript."
	::= { ltmHttpCompressionProfileStatEntry 9 }

ltmHttpCompressionProfileStatJsPostcompressBytes OBJECT-TYPE
	SYNTAX Counter64
	MAX-ACCESS read-only
	STATUS current
	DESCRIPTION
		"The number of post-compressed bytes for the MIME-Types: Javascript."
	::= { ltmHttpCompressionProfileStatEntry 10 }

ltmHttpCompressionProfileStatXmlPrecompressBytes OBJECT-TYPE
	SYNTAX Counter64
	MAX-ACCESS read-only
	STATUS current
	DESCRIPTION
		"The number of pre-compressed bytes for the MIME-Types: XML."
	::= { ltmHttpCompressionProfileStatEntry 11 }

ltmHttpCompressionProfileStatXmlPostcompressBytes OBJECT-TYPE
	SYNTAX Counter64
	MAX-ACCESS read-only
	STATUS current
	DESCRIPTION
		"The number of post-compressed bytes for the MIME-Types: XML."
	::= { ltmHttpCompressionProfileStatEntry 12 }

ltmHttpCompressionProfileStatSgmlPrecompressBytes OBJECT-TYPE
	SYNTAX Counter64
	MAX-ACCESS read-only
	STATUS current
	DESCRIPTION
		"The number of pre-compressed bytes for the MIME-Types: SGML."
	::= { ltmHttpCompressionProfileStatEntry 13 }

ltmHttpCompressionProfileStatSgmlPostcompressBytes OBJECT-TYPE
	SYNTAX Counter64
	MAX-ACCESS read-only
	STATUS current
	DESCRIPTION
		"The number of post-compressed bytes for the MIME-Types: SGML."
	::= { ltmHttpCompressionProfileStatEntry 14 }

ltmHttpCompressionProfileStatPlainPrecompressBytes OBJECT-TYPE
	SYNTAX Counter64
	MAX-ACCESS read-only
	STATUS current
	DESCRIPTION
		"The number of pre-compressed bytes for the MIME-Types: Plain."
	::= { ltmHttpCompressionProfileStatEntry 15 }

ltmHttpCompressionProfileStatPlainPostcompressBytes OBJECT-TYPE
	SYNTAX Counter64
	MAX-ACCESS read-only
	STATUS current
	DESCRIPTION
		"The number of post-compressed bytes for the MIME-Types: Plain."
	::= { ltmHttpCompressionProfileStatEntry 16 }

ltmHttpCompressionProfileStatOctetPrecompressBytes OBJECT-TYPE
	SYNTAX Counter64
	MAX-ACCESS read-only
	STATUS current
	DESCRIPTION
		"The number of pre-compressed bytes for the MIME-Types: Octet stream."
	::= { ltmHttpCompressionProfileStatEntry 17 }

ltmHttpCompressionProfileStatOctetPostcompressBytes OBJECT-TYPE
	SYNTAX Counter64
	MAX-ACCESS read-only
	STATUS current
	DESCRIPTION
		"The number of post-compressed bytes for the MIME-Types: Octet stream."
	::= { ltmHttpCompressionProfileStatEntry 18 }

ltmHttpCompressionProfileStatImagePrecompressBytes OBJECT-TYPE
	SYNTAX Counter64
	MAX-ACCESS read-only
	STATUS current
	DESCRIPTION
		"The number of pre-compressed bytes for the MIME-Types: Images."
	::= { ltmHttpCompressionProfileStatEntry 19 }

ltmHttpCompressionProfileStatImagePostcompressBytes OBJECT-TYPE
	SYNTAX Counter64
	MAX-ACCESS read-only
	STATUS current
	DESCRIPTION
		"The number of post-compressed bytes for the MIME-Types: Images."
	::= { ltmHttpCompressionProfileStatEntry 20 }

ltmHttpCompressionProfileStatVideoPrecompressBytes OBJECT-TYPE
	SYNTAX Counter64
	MAX-ACCESS read-only
	STATUS current
	DESCRIPTION
		"The number of pre-compressed bytes for the MIME-Types: Video files."
	::= { ltmHttpCompressionProfileStatEntry 21 }

ltmHttpCompressionProfileStatVideoPostcompressBytes OBJECT-TYPE
	SYNTAX Counter64
	MAX-ACCESS read-only
	STATUS current
	DESCRIPTION
		"The number of post-compressed bytes for the MIME-Types: Video files."
	::= { ltmHttpCompressionProfileStatEntry 22 }

ltmHttpCompressionProfileStatAudioPrecompressBytes OBJECT-TYPE
	SYNTAX Counter64
	MAX-ACCESS read-only
	STATUS current
	DESCRIPTION
		"The number of pre-compressed bytes for the MIME-Types: Audio files."
	::= { ltmHttpCompressionProfileStatEntry 23 }

ltmHttpCompressionProfileStatAudioPostcompressBytes OBJECT-TYPE
	SYNTAX Counter64
	MAX-ACCESS read-only
	STATUS current
	DESCRIPTION
		"The number of post-compressed bytes for the MIME-Types: Audio files."
	::= { ltmHttpCompressionProfileStatEntry 24 }

ltmHttpCompressionProfileStatOtherPrecompressBytes OBJECT-TYPE
	SYNTAX Counter64
	MAX-ACCESS read-only
	STATUS current
	DESCRIPTION
		"The number of pre-compressed bytes for the MIME-Types: other than
		HTML, CSS, Javascript, XML, SGML, Plain, Images, Video files,
		Audio files."
	::= { ltmHttpCompressionProfileStatEntry 25 }

ltmHttpCompressionProfileStatOtherPostcompressBytes OBJECT-TYPE
	SYNTAX Counter64
	MAX-ACCESS read-only
	STATUS current
	DESCRIPTION
		"The number of post-compressed bytes for the MIME-Types: other than
		HTML, CSS, Javascript, XML, SGML, Plain, Images, Video files,
		Audio files."
	::= { ltmHttpCompressionProfileStatEntry 26 }

--==================================================================
-- Profile_webacceleration
--==================================================================
ltmWebAccelerationProfileNumber OBJECT-TYPE
	SYNTAX INTEGER
	MAX-ACCESS read-only
	STATUS current
	DESCRIPTION
		"The number of ltmWebAccelerationProfile entries in the table."
	::= { ltmWebAccelerationProfile 1 }

ltmWebAccelerationProfileTable OBJECT-TYPE
	SYNTAX SEQUENCE OF LtmWebAccelerationProfileEntry
	MAX-ACCESS not-accessible
	STATUS current
	DESCRIPTION
		"A table containing information of Web Acceleration profiles."
	::= { ltmWebAccelerationProfile 2 }

ltmWebAccelerationProfileEntry OBJECT-TYPE
	SYNTAX  LtmWebAccelerationProfileEntry
	MAX-ACCESS not-accessible
	STATUS current
	DESCRIPTION
		"Columns in the ltmWebAccelerationProfile Table"
	INDEX {
		ltmWebAccelerationProfileName
	}
	::= { ltmWebAccelerationProfileTable 1 }

LtmWebAccelerationProfileEntry ::=
	SEQUENCE {
        	ltmWebAccelerationProfileName                             LongDisplayString,
        	ltmWebAccelerationProfileConfigSource                     INTEGER,
        	ltmWebAccelerationProfileDefaultName                      LongDisplayString,
        	ltmWebAccelerationProfileCacheSize                        Gauge,
        	ltmWebAccelerationProfileCacheMaxEntries                  Gauge,
        	ltmWebAccelerationProfileCacheMaxAge                      Gauge,
        	ltmWebAccelerationProfileCacheObjectMinSize               Gauge,
        	ltmWebAccelerationProfileCacheObjectMaxSize               Gauge,
        	ltmWebAccelerationProfileCacheIgnoreClient                INTEGER,
        	ltmWebAccelerationProfileCacheAgingRate                   Gauge,
        	ltmWebAccelerationProfileCacheInsertAgeHeader             INTEGER
	}

ltmWebAccelerationProfileName OBJECT-TYPE
	SYNTAX LongDisplayString
	MAX-ACCESS read-only
	STATUS current
	DESCRIPTION
		"The name of a Web Acceleration profile."
	::= { ltmWebAccelerationProfileEntry 1 }

ltmWebAccelerationProfileConfigSource OBJECT-TYPE
	SYNTAX INTEGER {
		usercfg(0),
		basecfg(1)
	}
	MAX-ACCESS read-only
	STATUS current
	DESCRIPTION
		"The state that specifies whether this is a base/pre-configured profile
		or user defined profile."
	::= { ltmWebAccelerationProfileEntry 2 }

ltmWebAccelerationProfileDefaultName OBJECT-TYPE
	SYNTAX LongDisplayString
	MAX-ACCESS read-only
	STATUS current
	DESCRIPTION
		"The name of the profile from which the specified profile derives
		its attribute default values."
	::= { ltmWebAccelerationProfileEntry 3 }

ltmWebAccelerationProfileCacheSize OBJECT-TYPE
	SYNTAX Gauge
	MAX-ACCESS read-only
	STATUS current
	DESCRIPTION
		"The maximum cache size in MB's."
	::= { ltmWebAccelerationProfileEntry 4 }

ltmWebAccelerationProfileCacheMaxEntries OBJECT-TYPE
	SYNTAX Gauge
	MAX-ACCESS read-only
	STATUS current
	DESCRIPTION
		"The maximum cache entries."
	::= { ltmWebAccelerationProfileEntry 5 }

ltmWebAccelerationProfileCacheMaxAge OBJECT-TYPE
	SYNTAX Gauge
	MAX-ACCESS read-only
	STATUS current
	DESCRIPTION
		"The maximum age of cached object."
	::= { ltmWebAccelerationProfileEntry 6 }

ltmWebAccelerationProfileCacheObjectMinSize OBJECT-TYPE
	SYNTAX Gauge
	MAX-ACCESS read-only
	STATUS current
	DESCRIPTION
		"The minimum size requirement for cached object in bytes."
	::= { ltmWebAccelerationProfileEntry 7 }

ltmWebAccelerationProfileCacheObjectMaxSize OBJECT-TYPE
	SYNTAX Gauge
	MAX-ACCESS read-only
	STATUS current
	DESCRIPTION
		"The maximum size limitation for cached object in bytes."
	::= { ltmWebAccelerationProfileEntry 8 }

ltmWebAccelerationProfileCacheIgnoreClient OBJECT-TYPE
	SYNTAX INTEGER {
		none(0),
		maxage(1),
		all(2)
	}
	MAX-ACCESS read-only
	STATUS current
	DESCRIPTION
		"The state that determine whether cache ignores client cache."
	::= { ltmWebAccelerationProfileEntry 9 }

ltmWebAccelerationProfileCacheAgingRate OBJECT-TYPE
	SYNTAX Gauge
	MAX-ACCESS read-only
	STATUS current
	DESCRIPTION
		"The aging rate for the cache."
	::= { ltmWebAccelerationProfileEntry 10 }

ltmWebAccelerationProfileCacheInsertAgeHeader OBJECT-TYPE
	SYNTAX INTEGER {
		disable(0),
		enable(1)
	}
	MAX-ACCESS read-only
	STATUS current
	DESCRIPTION
		"The mode that indicates whether to insert the Age headers."
	::= { ltmWebAccelerationProfileEntry 11 }

--==================================================================
-- Profile_webacceleration_cache_uri_excludes
--==================================================================
ltmWebaccCacheUriExclNumber OBJECT-TYPE
	SYNTAX INTEGER
	MAX-ACCESS read-only
	STATUS current
	DESCRIPTION
		"The number of ltmWebAccelerationProfileUriExcl entries in the table."
	::= { ltmWebAccelerationProfileUriExcl 1 }

ltmWebaccCacheUriExclTable OBJECT-TYPE
	SYNTAX SEQUENCE OF LtmWebaccCacheUriExclEntry
	MAX-ACCESS not-accessible
	STATUS current
	DESCRIPTION
		"A table containing information of excludes URIs in
	    Web Acceleration profiles."
	::= { ltmWebAccelerationProfileUriExcl 2 }

ltmWebaccCacheUriExclEntry OBJECT-TYPE
	SYNTAX  LtmWebaccCacheUriExclEntry
	MAX-ACCESS not-accessible
	STATUS current
	DESCRIPTION
		"Columns in the ltmWebaccCacheUriExcl Table"
	INDEX {
		ltmWebaccCacheUriExclName,
		ltmWebaccCacheUriExclIndex
	}
	::= { ltmWebaccCacheUriExclTable 1 }

LtmWebaccCacheUriExclEntry ::=
	SEQUENCE {
        	ltmWebaccCacheUriExclName                                 LongDisplayString,
        	ltmWebaccCacheUriExclIndex                                INTEGER,
        	ltmWebaccCacheUriExclUri                                  LongDisplayString
	}

ltmWebaccCacheUriExclName OBJECT-TYPE
	SYNTAX LongDisplayString
	MAX-ACCESS read-only
	STATUS current
	DESCRIPTION
		"The name of a Web Acceleration profile."
	::= { ltmWebaccCacheUriExclEntry 1 }

ltmWebaccCacheUriExclIndex OBJECT-TYPE
	SYNTAX INTEGER(0..2147483647)
	MAX-ACCESS read-only
	STATUS current
	DESCRIPTION
		"The index of exclude URI for the specified profile."
	::= { ltmWebaccCacheUriExclEntry 2 }

ltmWebaccCacheUriExclUri OBJECT-TYPE
	SYNTAX LongDisplayString
	MAX-ACCESS read-only
	STATUS current
	DESCRIPTION
		"The exclude URI for the specified profile."
	::= { ltmWebaccCacheUriExclEntry 3 }

--==================================================================
-- Profile_webacceleration_cache_uri_includes
--==================================================================
ltmWebaccCacheUriInclNumber OBJECT-TYPE
	SYNTAX INTEGER
	MAX-ACCESS read-only
	STATUS current
	DESCRIPTION
		"The number of ltmWebAccelerationProfileUriIncl entries in the table."
	::= { ltmWebAccelerationProfileUriIncl 1 }

ltmWebaccCacheUriInclTable OBJECT-TYPE
	SYNTAX SEQUENCE OF LtmWebaccCacheUriInclEntry
	MAX-ACCESS not-accessible
	STATUS current
	DESCRIPTION
		"A table containing information of includes URI in Web Acceleration
	    profiles."
	::= { ltmWebAccelerationProfileUriIncl 2 }

ltmWebaccCacheUriInclEntry OBJECT-TYPE
	SYNTAX  LtmWebaccCacheUriInclEntry
	MAX-ACCESS not-accessible
	STATUS current
	DESCRIPTION
		"Columns in the ltmWebaccCacheUriIncl Table"
	INDEX {
		ltmWebaccCacheUriInclName,
		ltmWebaccCacheUriInclIndex
	}
	::= { ltmWebaccCacheUriInclTable 1 }

LtmWebaccCacheUriInclEntry ::=
	SEQUENCE {
        	ltmWebaccCacheUriInclName                                 LongDisplayString,
        	ltmWebaccCacheUriInclIndex                                INTEGER,
        	ltmWebaccCacheUriInclUri                                  LongDisplayString
	}

ltmWebaccCacheUriInclName OBJECT-TYPE
	SYNTAX LongDisplayString
	MAX-ACCESS read-only
	STATUS current
	DESCRIPTION
		"The name of a Web Acceleration profile."
	::= { ltmWebaccCacheUriInclEntry 1 }

ltmWebaccCacheUriInclIndex OBJECT-TYPE
	SYNTAX INTEGER(0..2147483647)
	MAX-ACCESS read-only
	STATUS current
	DESCRIPTION
		"The index of include URI for the specified profile."
	::= { ltmWebaccCacheUriInclEntry 2 }

ltmWebaccCacheUriInclUri OBJECT-TYPE
	SYNTAX LongDisplayString
	MAX-ACCESS read-only
	STATUS current
	DESCRIPTION
		"The include URI for the specified profile."
	::= { ltmWebaccCacheUriInclEntry 3 }

--==================================================================
-- Profile_webacceleration_cache_uri_pinned
--==================================================================
ltmWebaccCacheUriPinNumber OBJECT-TYPE
	SYNTAX INTEGER
	MAX-ACCESS read-only
	STATUS current
	DESCRIPTION
		"The number of ltmWebAccelerationProfileUriPin entries in the table."
	::= { ltmWebAccelerationProfileUriPin 1 }

ltmWebaccCacheUriPinTable OBJECT-TYPE
	SYNTAX SEQUENCE OF LtmWebaccCacheUriPinEntry
	MAX-ACCESS not-accessible
	STATUS current
	DESCRIPTION
		"A table containing information of pinned URIs in Web Acceleration profiles."
	::= { ltmWebAccelerationProfileUriPin 2 }

ltmWebaccCacheUriPinEntry OBJECT-TYPE
	SYNTAX  LtmWebaccCacheUriPinEntry
	MAX-ACCESS not-accessible
	STATUS current
	DESCRIPTION
		"Columns in the ltmWebaccCacheUriPin Table"
	INDEX {
		ltmWebaccCacheUriPinName,
		ltmWebaccCacheUriPinIndex
	}
	::= { ltmWebaccCacheUriPinTable 1 }

LtmWebaccCacheUriPinEntry ::=
	SEQUENCE {
        	ltmWebaccCacheUriPinName                                  LongDisplayString,
        	ltmWebaccCacheUriPinIndex                                 INTEGER,
        	ltmWebaccCacheUriPinUri                                   LongDisplayString
	}

ltmWebaccCacheUriPinName OBJECT-TYPE
	SYNTAX LongDisplayString
	MAX-ACCESS read-only
	STATUS current
	DESCRIPTION
		"The name of a Web Acceleration profile."
	::= { ltmWebaccCacheUriPinEntry 1 }

ltmWebaccCacheUriPinIndex OBJECT-TYPE
	SYNTAX INTEGER(0..2147483647)
	MAX-ACCESS read-only
	STATUS current
	DESCRIPTION
		"The index of pinned URI for the specified profile."
	::= { ltmWebaccCacheUriPinEntry 2 }

ltmWebaccCacheUriPinUri OBJECT-TYPE
	SYNTAX LongDisplayString
	MAX-ACCESS read-only
	STATUS current
	DESCRIPTION
		"The pinned URI for the specified profile."
	::= { ltmWebaccCacheUriPinEntry 3 }

--==================================================================
-- Profile_webacceleration_stat
--==================================================================
ltmWebAccelerationProfileStatResetStats OBJECT-TYPE
	SYNTAX INTEGER
	MAX-ACCESS read-write
	STATUS current
	DESCRIPTION
		"The action to reset resettable statistics data in ltmWebAccelerationProfileStat.
		 Setting this value to 1 will reset statistics data.
		 Note, some statistics data may not be reset including data that are incremental counters."
	::= { ltmWebAccelerationProfileStat 1 }

ltmWebAccelerationProfileStatNumber OBJECT-TYPE
	SYNTAX INTEGER
	MAX-ACCESS read-only
	STATUS current
	DESCRIPTION
		"The number of ltmWebAccelerationProfileStat entries in the table."
	::= { ltmWebAccelerationProfileStat 2 }

ltmWebAccelerationProfileStatTable OBJECT-TYPE
	SYNTAX SEQUENCE OF LtmWebAccelerationProfileStatEntry
	MAX-ACCESS not-accessible
	STATUS current
	DESCRIPTION
		"A table containing statistic information of Web Acceleration profiles."
	::= { ltmWebAccelerationProfileStat 3 }

ltmWebAccelerationProfileStatEntry OBJECT-TYPE
	SYNTAX  LtmWebAccelerationProfileStatEntry
	MAX-ACCESS not-accessible
	STATUS current
	DESCRIPTION
		"Columns in the ltmWebAccelerationProfileStat Table"
	INDEX {
		ltmWebAccelerationProfileStatName
	}
	::= { ltmWebAccelerationProfileStatTable 1 }

LtmWebAccelerationProfileStatEntry ::=
	SEQUENCE {
        	ltmWebAccelerationProfileStatName                         LongDisplayString,
        	ltmWebAccelerationProfileStatCacheHits                    Counter64,
        	ltmWebAccelerationProfileStatCacheMisses                  Counter64,
        	ltmWebAccelerationProfileStatCacheMissesAll               Counter64,
        	ltmWebAccelerationProfileStatCacheHitBytes                Counter64,
        	ltmWebAccelerationProfileStatCacheMissBytes               Counter64,
        	ltmWebAccelerationProfileStatCacheMissBytesAll            Counter64,
        	ltmWebAccelerationProfileStatCacheSize                    Counter64,
        	ltmWebAccelerationProfileStatCacheCount                   Counter64,
        	ltmWebAccelerationProfileStatCacheEvictions               Counter64,
        	ltmWebAccelerationProfileStatInterStripeHits              Counter64,
        	ltmWebAccelerationProfileStatInterStripeMisses            Counter64,
        	ltmWebAccelerationProfileStatInterStripeHitBytes          Counter64,
        	ltmWebAccelerationProfileStatInterStripeSize              Counter64,
        	ltmWebAccelerationProfileStatInterStripeCount             Counter64,
        	ltmWebAccelerationProfileStatInterStripeEvictions         Counter64,
        	ltmWebAccelerationProfileStatRemoteHits                   Counter64,
        	ltmWebAccelerationProfileStatRemoteMisses                 Counter64,
        	ltmWebAccelerationProfileStatRemoteHitBytes               Counter64
	}

ltmWebAccelerationProfileStatName OBJECT-TYPE
	SYNTAX LongDisplayString
	MAX-ACCESS read-only
	STATUS current
	DESCRIPTION
		"The name of a Web Acceleration profile."
	::= { ltmWebAccelerationProfileStatEntry 1 }

ltmWebAccelerationProfileStatCacheHits OBJECT-TYPE
	SYNTAX Counter64
	MAX-ACCESS read-only
	STATUS current
	DESCRIPTION
		"The number of cache hits."
	::= { ltmWebAccelerationProfileStatEntry 2 }

ltmWebAccelerationProfileStatCacheMisses OBJECT-TYPE
	SYNTAX Counter64
	MAX-ACCESS read-only
	STATUS current
	DESCRIPTION
		"The number of cache misses, excluding un-cacheable data."
	::= { ltmWebAccelerationProfileStatEntry 3 }

ltmWebAccelerationProfileStatCacheMissesAll OBJECT-TYPE
	SYNTAX Counter64
	MAX-ACCESS read-only
	STATUS current
	DESCRIPTION
		"The total number of cache misses."
	::= { ltmWebAccelerationProfileStatEntry 4 }

ltmWebAccelerationProfileStatCacheHitBytes OBJECT-TYPE
	SYNTAX Counter64
	MAX-ACCESS read-only
	STATUS current
	DESCRIPTION
		"The number of cache hits in bytes."
	::= { ltmWebAccelerationProfileStatEntry 5 }

ltmWebAccelerationProfileStatCacheMissBytes OBJECT-TYPE
	SYNTAX Counter64
	MAX-ACCESS read-only
	STATUS current
	DESCRIPTION
		"The number of cache misses in bytes, excluding un-cacheable data."
	::= { ltmWebAccelerationProfileStatEntry 6 }

ltmWebAccelerationProfileStatCacheMissBytesAll OBJECT-TYPE
	SYNTAX Counter64
	MAX-ACCESS read-only
	STATUS current
	DESCRIPTION
		"The total number of cache misses in bytes."
	::= { ltmWebAccelerationProfileStatEntry 7 }

ltmWebAccelerationProfileStatCacheSize OBJECT-TYPE
	SYNTAX Counter64
	MAX-ACCESS read-only
	STATUS current
	DESCRIPTION
		"The current cache size (in bytes)."
	::= { ltmWebAccelerationProfileStatEntry 8 }

ltmWebAccelerationProfileStatCacheCount OBJECT-TYPE
	SYNTAX Counter64
	MAX-ACCESS read-only
	STATUS current
	DESCRIPTION
		"The number of items stored in cache."
	::= { ltmWebAccelerationProfileStatEntry 9 }

ltmWebAccelerationProfileStatCacheEvictions OBJECT-TYPE
	SYNTAX Counter64
	MAX-ACCESS read-only
	STATUS current
	DESCRIPTION
		"The number of cache evictions."
	::= { ltmWebAccelerationProfileStatEntry 10 }

ltmWebAccelerationProfileStatInterStripeHits OBJECT-TYPE
	SYNTAX Counter64
	MAX-ACCESS read-only
	STATUS current
	DESCRIPTION
		"The number of inter-stripe cache hits."
	::= { ltmWebAccelerationProfileStatEntry 11 }

ltmWebAccelerationProfileStatInterStripeMisses OBJECT-TYPE
	SYNTAX Counter64
	MAX-ACCESS read-only
	STATUS current
	DESCRIPTION
		"The number of inter-stripe cache misses."
	::= { ltmWebAccelerationProfileStatEntry 12 }

ltmWebAccelerationProfileStatInterStripeHitBytes OBJECT-TYPE
	SYNTAX Counter64
	MAX-ACCESS read-only
	STATUS current
	DESCRIPTION
		"The number of inter-stripe cache hits in bytes."
	::= { ltmWebAccelerationProfileStatEntry 13 }

ltmWebAccelerationProfileStatInterStripeSize OBJECT-TYPE
	SYNTAX Counter64
	MAX-ACCESS read-only
	STATUS current
	DESCRIPTION
		"The current inter-stripe cache size (in bytes)."
	::= { ltmWebAccelerationProfileStatEntry 14 }

ltmWebAccelerationProfileStatInterStripeCount OBJECT-TYPE
	SYNTAX Counter64
	MAX-ACCESS read-only
	STATUS current
	DESCRIPTION
		"The number of items stored in inter-stripe cache."
	::= { ltmWebAccelerationProfileStatEntry 15 }

ltmWebAccelerationProfileStatInterStripeEvictions OBJECT-TYPE
	SYNTAX Counter64
	MAX-ACCESS read-only
	STATUS current
	DESCRIPTION
		"The number of inter-stripe cache evictions."
	::= { ltmWebAccelerationProfileStatEntry 16 }

ltmWebAccelerationProfileStatRemoteHits OBJECT-TYPE
	SYNTAX Counter64
	MAX-ACCESS read-only
	STATUS current
	DESCRIPTION
		"The number of remote cache hits."
	::= { ltmWebAccelerationProfileStatEntry 17 }

ltmWebAccelerationProfileStatRemoteMisses OBJECT-TYPE
	SYNTAX Counter64
	MAX-ACCESS read-only
	STATUS current
	DESCRIPTION
		"The number of remote cache misses."
	::= { ltmWebAccelerationProfileStatEntry 18 }

ltmWebAccelerationProfileStatRemoteHitBytes OBJECT-TYPE
	SYNTAX Counter64
	MAX-ACCESS read-only
	STATUS current
	DESCRIPTION
		"The number of remote cache hits in bytes."
	::= { ltmWebAccelerationProfileStatEntry 19 }

--==================================================================
-- Rst_cause_stat
--==================================================================
ltmRstCauseStatResetStats OBJECT-TYPE
	SYNTAX INTEGER
	MAX-ACCESS read-write
	STATUS current
	DESCRIPTION
		"The action to reset resettable statistics data in ltmRstCauseStat.
		 Setting this value to 1 will reset statistics data.
		 Note, some statistics data may not be reset including data that are incremental counters."
	::= { ltmRstCauseStat 1 }

ltmRstCauseStatNumber OBJECT-TYPE
	SYNTAX INTEGER
	MAX-ACCESS read-only
	STATUS current
	DESCRIPTION
		"The number of ltmRstCauseStat entries in the table."
	::= { ltmRstCauseStat 2 }

ltmRstCauseStatTable OBJECT-TYPE
	SYNTAX SEQUENCE OF LtmRstCauseStatEntry
	MAX-ACCESS not-accessible
	STATUS current
	DESCRIPTION
		"A table containing statistics for TCP/IP reset (RST) causes."
	::= { ltmRstCauseStat 3 }

ltmRstCauseStatEntry OBJECT-TYPE
	SYNTAX  LtmRstCauseStatEntry
	MAX-ACCESS not-accessible
	STATUS current
	DESCRIPTION
		"Columns in the ltmRstCauseStat Table"
	INDEX {
		ltmRstCauseStatIndex
	}
	::= { ltmRstCauseStatTable 1 }

LtmRstCauseStatEntry ::=
	SEQUENCE {
        	ltmRstCauseStatIndex                                      INTEGER,
        	ltmRstCauseStatRstCause                                   LongDisplayString,
        	ltmRstCauseStatCount                                      Counter64
	}

ltmRstCauseStatIndex OBJECT-TYPE
	SYNTAX INTEGER(0..2147483647)
	MAX-ACCESS read-only
	STATUS current
	DESCRIPTION
		"The index of cause of TCP/IP reset."
	::= { ltmRstCauseStatEntry 1 }

ltmRstCauseStatRstCause OBJECT-TYPE
	SYNTAX LongDisplayString
	MAX-ACCESS read-only
	STATUS current
	DESCRIPTION
		"The cause for TCP/IP reset (RST)."
	::= { ltmRstCauseStatEntry 2 }

ltmRstCauseStatCount OBJECT-TYPE
	SYNTAX Counter64
	MAX-ACCESS read-only
	STATUS current
	DESCRIPTION
		"The count for each TCP/IP reset (RST) cause."
	::= { ltmRstCauseStatEntry 3 }

--==================================================================
-- Profile_webacceleration_cache_uri_include_overrides
--==================================================================
ltmWebaccCacheUriOverNumber OBJECT-TYPE
	SYNTAX INTEGER
	MAX-ACCESS read-only
	STATUS current
	DESCRIPTION
		"The number of ltmWebAccelerationProfileUriOver entries in the table."
	::= { ltmWebAccelerationProfileUriOver 1 }

ltmWebaccCacheUriOverTable OBJECT-TYPE
	SYNTAX SEQUENCE OF LtmWebaccCacheUriOverEntry
	MAX-ACCESS not-accessible
	STATUS current
	DESCRIPTION
		"A table containing information of include override URI in Web Acceleration profiles."
	::= { ltmWebAccelerationProfileUriOver 2 }

ltmWebaccCacheUriOverEntry OBJECT-TYPE
	SYNTAX  LtmWebaccCacheUriOverEntry
	MAX-ACCESS not-accessible
	STATUS current
	DESCRIPTION
		"Columns in the ltmWebaccCacheUriOver Table"
	INDEX {
		ltmWebaccCacheUriOverName,
		ltmWebaccCacheUriOverIndex
	}
	::= { ltmWebaccCacheUriOverTable 1 }

LtmWebaccCacheUriOverEntry ::=
	SEQUENCE {
        	ltmWebaccCacheUriOverName                                 LongDisplayString,
        	ltmWebaccCacheUriOverIndex                                INTEGER,
        	ltmWebaccCacheUriOverUri                                  LongDisplayString
	}

ltmWebaccCacheUriOverName OBJECT-TYPE
	SYNTAX LongDisplayString
	MAX-ACCESS read-only
	STATUS current
	DESCRIPTION
		"The name of a Web Acceleration profile."
	::= { ltmWebaccCacheUriOverEntry 1 }

ltmWebaccCacheUriOverIndex OBJECT-TYPE
	SYNTAX INTEGER(0..2147483647)
	MAX-ACCESS read-only
	STATUS current
	DESCRIPTION
		"The index of include override URI for the specified profile."
	::= { ltmWebaccCacheUriOverEntry 2 }

ltmWebaccCacheUriOverUri OBJECT-TYPE
	SYNTAX LongDisplayString
	MAX-ACCESS read-only
	STATUS current
	DESCRIPTION
		"The include override URI for the specified profile."
	::= { ltmWebaccCacheUriOverEntry 3 }

--==================================================================
-- Dns_cache_resolver
--==================================================================
ltmDnsCacheNumber OBJECT-TYPE
	SYNTAX INTEGER
	MAX-ACCESS read-only
	STATUS current
	DESCRIPTION
		"The number of ltmDnsCache entries in the table."
	::= { ltmDnsCache 1 }

ltmDnsCacheTable OBJECT-TYPE
	SYNTAX SEQUENCE OF LtmDnsCacheEntry
	MAX-ACCESS not-accessible
	STATUS current
	DESCRIPTION
		"A table containing information of DNS cache."
	::= { ltmDnsCache 2 }

ltmDnsCacheEntry OBJECT-TYPE
	SYNTAX  LtmDnsCacheEntry
	MAX-ACCESS not-accessible
	STATUS current
	DESCRIPTION
		"Columns in the ltmDnsCache Table"
	INDEX {
		ltmDnsCacheName
	}
	::= { ltmDnsCacheTable 1 }

LtmDnsCacheEntry ::=
	SEQUENCE {
        	ltmDnsCacheName                                           LongDisplayString,
        	ltmDnsCacheType                                           INTEGER,
        	ltmDnsCacheMsgCacheSize                                   Gauge,
        	ltmDnsCacheRrsetCacheSize                                 Gauge,
        	ltmDnsCacheAnswerDefaultZones                             INTEGER,
        	ltmDnsCacheUseIpv4                                        INTEGER,
        	ltmDnsCacheUseIpv6                                        INTEGER,
        	ltmDnsCacheUseUdp                                         INTEGER,
        	ltmDnsCacheUseTcp                                         INTEGER,
        	ltmDnsCacheNameserverCacheCount                           Gauge,
        	ltmDnsCacheMaxConcurrentTcp                               Gauge,
        	ltmDnsCacheMaxConcurrentUdp                               Gauge,
        	ltmDnsCacheUnwantedThreshold                              Gauge,
        	ltmDnsCacheRouteDomainName                                LongDisplayString,
        	ltmDnsCacheIgnoreCd                                       INTEGER,
        	ltmDnsCachePrefetchKey                                    INTEGER,
        	ltmDnsCacheKeyCacheSize                                   Gauge,
        	ltmDnsCacheRandomizeQueryNameCase                         INTEGER,
        	ltmDnsCacheMaxConcurrentQueries                           Gauge,
        	ltmDnsCacheAllowedQueryTime                               Gauge
	}

ltmDnsCacheName OBJECT-TYPE
	SYNTAX LongDisplayString
	MAX-ACCESS read-only
	STATUS current
	DESCRIPTION
		"The name of DNS cache."
	::= { ltmDnsCacheEntry 1 }

ltmDnsCacheType OBJECT-TYPE
	SYNTAX INTEGER {
		resolver(0),
		validatingResolver(1),
		transparentResolver(2)
	}
	MAX-ACCESS read-only
	STATUS current
	DESCRIPTION
		"The type of DNS cache.
		 resolver - configures a DNS cache with a resolver on the BIG-IP system;
		 validatingResolver - configures a DNS cache with a resolver and
		 validator on the BIG-IP system;
		 transparentResolver - configures a DNS cache without a resolver
		 on the BIG-IP system."
	::= { ltmDnsCacheEntry 2 }

ltmDnsCacheMsgCacheSize OBJECT-TYPE
	SYNTAX Gauge
	MAX-ACCESS read-only
	STATUS current
	DESCRIPTION
		"The number of bytes allocated to the message cache. The default
		value is 1m. Relevant to resolver, validatingResolver, and
		transparentResolver types."
	::= { ltmDnsCacheEntry 3 }

ltmDnsCacheRrsetCacheSize OBJECT-TYPE
	SYNTAX Gauge
	MAX-ACCESS read-only
	STATUS current
	DESCRIPTION
		"The number of bytes allocated to the resource records set cache.
		The default value is 10m. Relevant to resolver, validatingResolver,
		and transparentResolver types."
	::= { ltmDnsCacheEntry 4 }

ltmDnsCacheAnswerDefaultZones OBJECT-TYPE
	SYNTAX INTEGER {
		no(0),
		yes(1)
	}
	MAX-ACCESS read-only
	STATUS current
	DESCRIPTION
		"The state indicating whether or not the resolver answers queries for
		default zones: localhost, reverse 127.0.0.1 and ::1, and AS112 zones.
		The default value is no. Relevant to resolver, validatingResolver,
		and transparentResolver types."
	::= { ltmDnsCacheEntry 5 }

ltmDnsCacheUseIpv4 OBJECT-TYPE
	SYNTAX INTEGER {
		no(0),
		yes(1)
	}
	MAX-ACCESS read-only
	STATUS current
	DESCRIPTION
		"The state indicating whether or not the resolver is enabled to
		send queries to IPv4 addresses. The default value is yes. Relevant
		to resolver and validatingResolver types."
	::= { ltmDnsCacheEntry 6 }

ltmDnsCacheUseIpv6 OBJECT-TYPE
	SYNTAX INTEGER {
		no(0),
		yes(1)
	}
	MAX-ACCESS read-only
	STATUS current
	DESCRIPTION
		"The state indicating whether or not the resolver is enabled to
		send queries to IPv6 addresses. The default value is yes. Relevant
		to resolver and validatingResolver types."
	::= { ltmDnsCacheEntry 7 }

ltmDnsCacheUseUdp OBJECT-TYPE
	SYNTAX INTEGER {
		no(0),
		yes(1)
	}
	MAX-ACCESS read-only
	STATUS current
	DESCRIPTION
		"The state indicating whether or not the resolver is enabled to
		send queries over UDP. The default value is yes. Relevant to
		resolver and validatingResolver types."
	::= { ltmDnsCacheEntry 8 }

ltmDnsCacheUseTcp OBJECT-TYPE
	SYNTAX INTEGER {
		no(0),
		yes(1)
	}
	MAX-ACCESS read-only
	STATUS current
	DESCRIPTION
		"The state indicating whether or not the resolver is enabled to
		send queries over TCP. The default value is yes. Relevant to
		resolver and validatingResolver types."
	::= { ltmDnsCacheEntry 9 }

ltmDnsCacheNameserverCacheCount OBJECT-TYPE
	SYNTAX Gauge
	MAX-ACCESS read-only
	STATUS current
	DESCRIPTION
		"The number of DNS name-servers for which connection and capability
		data is cached. The default value is 16k. Relevant to resolver and
		validatingResolver types."
	::= { ltmDnsCacheEntry 10 }

ltmDnsCacheMaxConcurrentTcp OBJECT-TYPE
	SYNTAX Gauge
	MAX-ACCESS read-only
	STATUS current
	DESCRIPTION
		"The maximum number of concurrent TCP flows used by the resolver.
		The default value is 20. Relevant to resolver and validatingResolver
		types."
	::= { ltmDnsCacheEntry 11 }

ltmDnsCacheMaxConcurrentUdp OBJECT-TYPE
	SYNTAX Gauge
	MAX-ACCESS read-only
	STATUS current
	DESCRIPTION
		"The maximum number of concurrent UDP flows used by the resolver.
		The default value is 8192. Relevant to resolver and
		validatingResolver types."
	::= { ltmDnsCacheEntry 12 }

ltmDnsCacheUnwantedThreshold OBJECT-TYPE
	SYNTAX Gauge
	MAX-ACCESS read-only
	STATUS current
	DESCRIPTION
		"The threshold count of unsolicited query replies which triggers
		an alert (potential DOS attack underway). The default value is
		zero (or off). Relevant to resolver and validatingResolver types."
	::= { ltmDnsCacheEntry 13 }

ltmDnsCacheRouteDomainName OBJECT-TYPE
	SYNTAX LongDisplayString
	MAX-ACCESS read-only
	STATUS current
	DESCRIPTION
		"The name of the route domain used for resolver outbound traffic.
		The default value is the default route domain. Relevant to resolver
		and validatingResolver types."
	::= { ltmDnsCacheEntry 14 }

ltmDnsCacheIgnoreCd OBJECT-TYPE
	SYNTAX INTEGER {
		no(0),
		yes(1)
	}
	MAX-ACCESS read-only
	STATUS current
	DESCRIPTION
		"The state indicating whether or not the validatingResolver ignores
		client queries setting of checking-disabled and performs validation
		anyway and only returns secure answers. The default value is no.
		Relevant to validatingResolver type."
	::= { ltmDnsCacheEntry 15 }

ltmDnsCachePrefetchKey OBJECT-TYPE
	SYNTAX INTEGER {
		no(0),
		yes(1)
	}
	MAX-ACCESS read-only
	STATUS current
	DESCRIPTION
		"The state indicating whether or not the validatingResolver fetches
		DNSKEY early in validation process. The default value is yes.
		Relevant to validatingResolver type."
	::= { ltmDnsCacheEntry 16 }

ltmDnsCacheKeyCacheSize OBJECT-TYPE
	SYNTAX Gauge
	MAX-ACCESS read-only
	STATUS current
	DESCRIPTION
		"The number of bytes allocated to the DNSKEY cache. The default
		value is 1m. Relevant to validatingResolver type."
	::= { ltmDnsCacheEntry 17 }

ltmDnsCacheRandomizeQueryNameCase OBJECT-TYPE
	SYNTAX INTEGER {
		no(0),
		yes(1)
	}
	MAX-ACCESS read-only
	STATUS current
	DESCRIPTION
		"The state indicating whether or not the resolver is enabled to randomize
	        the case of query names. The default value is yes. Relevant to resolver
	        and validatingResolver types."
	::= { ltmDnsCacheEntry 18 }

ltmDnsCacheMaxConcurrentQueries OBJECT-TYPE
	SYNTAX Gauge
	MAX-ACCESS read-only
	STATUS current
	DESCRIPTION
		"The maximum number of concurrent distinct queries used
	        by the resolver. A query is identified by query name, type and class.
	        If the number of distinct queries exceeds this limit, the resolver
	        will try to find a query from the queue which arrives the earliest.
	        Replace it with the new query if it has been in the queue longer than
	        the allowed time. The default value is 1024."
	::= { ltmDnsCacheEntry 19 }

ltmDnsCacheAllowedQueryTime OBJECT-TYPE
	SYNTAX Gauge
	MAX-ACCESS read-only
	STATUS current
	DESCRIPTION
		"The time allowed for a query to stay in the queue before replaced by
	        a new query when the number of concurrent distinct queries exceeds
	        the limit. The default value is 200 milliseconds."
	::= { ltmDnsCacheEntry 20 }

--==================================================================
-- Dns_cache_resolver_stat
--==================================================================
ltmDnsCacheStatResetStats OBJECT-TYPE
	SYNTAX INTEGER
	MAX-ACCESS read-write
	STATUS current
	DESCRIPTION
		"The action to reset resettable statistics data in ltmDnsCacheStat.
		 Setting this value to 1 will reset statistics data.
		 Note, some statistics data may not be reset including data that are incremental counters."
	::= { ltmDnsCacheStat 1 }

ltmDnsCacheStatNumber OBJECT-TYPE
	SYNTAX INTEGER
	MAX-ACCESS read-only
	STATUS current
	DESCRIPTION
		"The number of ltmDnsCacheStat entries in the table."
	::= { ltmDnsCacheStat 2 }

ltmDnsCacheStatTable OBJECT-TYPE
	SYNTAX SEQUENCE OF LtmDnsCacheStatEntry
	MAX-ACCESS not-accessible
	STATUS current
	DESCRIPTION
		"A table containing statistics information of DNS cache."
	::= { ltmDnsCacheStat 3 }

ltmDnsCacheStatEntry OBJECT-TYPE
	SYNTAX  LtmDnsCacheStatEntry
	MAX-ACCESS not-accessible
	STATUS current
	DESCRIPTION
		"Columns in the ltmDnsCacheStat Table"
	INDEX {
		ltmDnsCacheStatName
	}
	::= { ltmDnsCacheStatTable 1 }

LtmDnsCacheStatEntry ::=
	SEQUENCE {
        	ltmDnsCacheStatName                                       LongDisplayString,
        	ltmDnsCacheStatQueries                                    Counter64,
        	ltmDnsCacheStatResponses                                  Counter64,
        	ltmDnsCacheStatSync                                       Counter64,
        	ltmDnsCacheStatAsync                                      Counter64,
        	ltmDnsCacheStatFailureResolv                              Counter64,
        	ltmDnsCacheStatFailureCf                                  Counter64,
        	ltmDnsCacheStatFailureServer                              Counter64,
        	ltmDnsCacheStatFailureSend                                Counter64,
        	ltmDnsCacheStatMsgHits                                    Counter64,
        	ltmDnsCacheStatMsgMisses                                  Counter64,
        	ltmDnsCacheStatMsgInserts                                 Counter64,
        	ltmDnsCacheStatMsgUpdates                                 Counter64,
        	ltmDnsCacheStatMsgEvictions                               Counter64,
        	ltmDnsCacheStatRrsetHits                                  Counter64,
        	ltmDnsCacheStatRrsetMisses                                Counter64,
        	ltmDnsCacheStatRrsetInserts                               Counter64,
        	ltmDnsCacheStatRrsetUpdates                               Counter64,
        	ltmDnsCacheStatRrsetEvictions                             Counter64,
        	ltmDnsCacheStatNameserverHits                             Counter64,
        	ltmDnsCacheStatNameserverMisses                           Counter64,
        	ltmDnsCacheStatNameserverInserts                          Counter64,
        	ltmDnsCacheStatNameserverUpdates                          Counter64,
        	ltmDnsCacheStatNameserverEvictions                        Counter64,
        	ltmDnsCacheStatKeyHits                                    Counter64,
        	ltmDnsCacheStatKeyMisses                                  Counter64,
        	ltmDnsCacheStatKeyInserts                                 Counter64,
        	ltmDnsCacheStatKeyUpdates                                 Counter64,
        	ltmDnsCacheStatKeyEvictions                               Counter64,
        	ltmDnsCacheStatUdpBytesIn                                 Counter64,
        	ltmDnsCacheStatUdpBytesOut                                Counter64,
        	ltmDnsCacheStatUdpPktsIn                                  Counter64,
        	ltmDnsCacheStatUdpPktsOut                                 Counter64,
        	ltmDnsCacheStatUdpCurConns                                Counter64,
        	ltmDnsCacheStatUdpMaxConns                                Counter64,
        	ltmDnsCacheStatUdpTotConns                                Counter64,
        	ltmDnsCacheStatTcpBytesIn                                 Counter64,
        	ltmDnsCacheStatTcpBytesOut                                Counter64,
        	ltmDnsCacheStatTcpPktsIn                                  Counter64,
        	ltmDnsCacheStatTcpPktsOut                                 Counter64,
        	ltmDnsCacheStatTcpCurConns                                Counter64,
        	ltmDnsCacheStatTcpMaxConns                                Counter64,
        	ltmDnsCacheStatTcpTotConns                                Counter64,
        	ltmDnsCacheStatUnsolicitedReplies                         Counter64,
        	ltmDnsCacheStatSecUnchecked                               Counter64,
        	ltmDnsCacheStatSecBogus                                   Counter64,
        	ltmDnsCacheStatSecIndeterminate                           Counter64,
        	ltmDnsCacheStatSecInsecure                                Counter64,
        	ltmDnsCacheStatSecSecure                                  Counter64,
        	ltmDnsCacheStatFwdQueries                                 Counter64,
        	ltmDnsCacheStatFwdResponses                               Counter64,
        	ltmDnsCacheStatRpzRewrites                                Counter64
	}

ltmDnsCacheStatName OBJECT-TYPE
	SYNTAX LongDisplayString
	MAX-ACCESS read-only
	STATUS current
	DESCRIPTION
		"The name of DNS cache."
	::= { ltmDnsCacheStatEntry 1 }

ltmDnsCacheStatQueries OBJECT-TYPE
	SYNTAX Counter64
	MAX-ACCESS read-only
	STATUS current
	DESCRIPTION
		"The total number of queries."
	::= { ltmDnsCacheStatEntry 2 }

ltmDnsCacheStatResponses OBJECT-TYPE
	SYNTAX Counter64
	MAX-ACCESS read-only
	STATUS current
	DESCRIPTION
		"The total number of responses."
	::= { ltmDnsCacheStatEntry 3 }

ltmDnsCacheStatSync OBJECT-TYPE
	SYNTAX Counter64
	MAX-ACCESS read-only
	STATUS current
	DESCRIPTION
		"The total number of synchronous responses."
	::= { ltmDnsCacheStatEntry 4 }

ltmDnsCacheStatAsync OBJECT-TYPE
	SYNTAX Counter64
	MAX-ACCESS read-only
	STATUS current
	DESCRIPTION
		"The total number of asynchronous responses."
	::= { ltmDnsCacheStatEntry 5 }

ltmDnsCacheStatFailureResolv OBJECT-TYPE
	SYNTAX Counter64
	MAX-ACCESS read-only
	STATUS current
	DESCRIPTION
		"The total number of internal resolution failures."
	::= { ltmDnsCacheStatEntry 6 }

ltmDnsCacheStatFailureCf OBJECT-TYPE
	SYNTAX Counter64
	MAX-ACCESS read-only
	STATUS current
	DESCRIPTION
		"The total number of internal connection failures."
	::= { ltmDnsCacheStatEntry 7 }

ltmDnsCacheStatFailureServer OBJECT-TYPE
	SYNTAX Counter64
	MAX-ACCESS read-only
	STATUS current
	DESCRIPTION
		"The total number of server core failures."
	::= { ltmDnsCacheStatEntry 8 }

ltmDnsCacheStatFailureSend OBJECT-TYPE
	SYNTAX Counter64
	MAX-ACCESS read-only
	STATUS current
	DESCRIPTION
		"The total number of response send failures."
	::= { ltmDnsCacheStatEntry 9 }

ltmDnsCacheStatMsgHits OBJECT-TYPE
	SYNTAX Counter64
	MAX-ACCESS read-only
	STATUS current
	DESCRIPTION
		"The number of complete message cache hits."
	::= { ltmDnsCacheStatEntry 10 }

ltmDnsCacheStatMsgMisses OBJECT-TYPE
	SYNTAX Counter64
	MAX-ACCESS read-only
	STATUS current
	DESCRIPTION
		"The number of complete message cache misses."
	::= { ltmDnsCacheStatEntry 11 }

ltmDnsCacheStatMsgInserts OBJECT-TYPE
	SYNTAX Counter64
	MAX-ACCESS read-only
	STATUS current
	DESCRIPTION
		"The number of complete message cache inserts."
	::= { ltmDnsCacheStatEntry 12 }

ltmDnsCacheStatMsgUpdates OBJECT-TYPE
	SYNTAX Counter64
	MAX-ACCESS read-only
	STATUS current
	DESCRIPTION
		"The number of complete message cache updates."
	::= { ltmDnsCacheStatEntry 13 }

ltmDnsCacheStatMsgEvictions OBJECT-TYPE
	SYNTAX Counter64
	MAX-ACCESS read-only
	STATUS current
	DESCRIPTION
		"The number of complete message cache evictions."
	::= { ltmDnsCacheStatEntry 14 }

ltmDnsCacheStatRrsetHits OBJECT-TYPE
	SYNTAX Counter64
	MAX-ACCESS read-only
	STATUS current
	DESCRIPTION
		"The number of resource record set cache hits."
	::= { ltmDnsCacheStatEntry 15 }

ltmDnsCacheStatRrsetMisses OBJECT-TYPE
	SYNTAX Counter64
	MAX-ACCESS read-only
	STATUS current
	DESCRIPTION
		"The number of resource record set cache misses."
	::= { ltmDnsCacheStatEntry 16 }

ltmDnsCacheStatRrsetInserts OBJECT-TYPE
	SYNTAX Counter64
	MAX-ACCESS read-only
	STATUS current
	DESCRIPTION
		"The number of resource record set cache inserts."
	::= { ltmDnsCacheStatEntry 17 }

ltmDnsCacheStatRrsetUpdates OBJECT-TYPE
	SYNTAX Counter64
	MAX-ACCESS read-only
	STATUS current
	DESCRIPTION
		"The number of resource record set cache updates."
	::= { ltmDnsCacheStatEntry 18 }

ltmDnsCacheStatRrsetEvictions OBJECT-TYPE
	SYNTAX Counter64
	MAX-ACCESS read-only
	STATUS current
	DESCRIPTION
		"The number of resource record set cache evictions."
	::= { ltmDnsCacheStatEntry 19 }

ltmDnsCacheStatNameserverHits OBJECT-TYPE
	SYNTAX Counter64
	MAX-ACCESS read-only
	STATUS current
	DESCRIPTION
		"The number of internet name-server cache hits."
	::= { ltmDnsCacheStatEntry 20 }

ltmDnsCacheStatNameserverMisses OBJECT-TYPE
	SYNTAX Counter64
	MAX-ACCESS read-only
	STATUS current
	DESCRIPTION
		"The number of internet name-server cache misses."
	::= { ltmDnsCacheStatEntry 21 }

ltmDnsCacheStatNameserverInserts OBJECT-TYPE
	SYNTAX Counter64
	MAX-ACCESS read-only
	STATUS current
	DESCRIPTION
		"The number of internet name-server cache inserts."
	::= { ltmDnsCacheStatEntry 22 }

ltmDnsCacheStatNameserverUpdates OBJECT-TYPE
	SYNTAX Counter64
	MAX-ACCESS read-only
	STATUS current
	DESCRIPTION
		"The number of internet name-server cache updates."
	::= { ltmDnsCacheStatEntry 23 }

ltmDnsCacheStatNameserverEvictions OBJECT-TYPE
	SYNTAX Counter64
	MAX-ACCESS read-only
	STATUS current
	DESCRIPTION
		"The number of internet name-server evictions."
	::= { ltmDnsCacheStatEntry 24 }

ltmDnsCacheStatKeyHits OBJECT-TYPE
	SYNTAX Counter64
	MAX-ACCESS read-only
	STATUS current
	DESCRIPTION
		"The number of DNSSEC key cache hits."
	::= { ltmDnsCacheStatEntry 25 }

ltmDnsCacheStatKeyMisses OBJECT-TYPE
	SYNTAX Counter64
	MAX-ACCESS read-only
	STATUS current
	DESCRIPTION
		"The number of DNSSEC key cache misses."
	::= { ltmDnsCacheStatEntry 26 }

ltmDnsCacheStatKeyInserts OBJECT-TYPE
	SYNTAX Counter64
	MAX-ACCESS read-only
	STATUS current
	DESCRIPTION
		"The number of DNSSEC key cache inserts."
	::= { ltmDnsCacheStatEntry 27 }

ltmDnsCacheStatKeyUpdates OBJECT-TYPE
	SYNTAX Counter64
	MAX-ACCESS read-only
	STATUS current
	DESCRIPTION
		"The number of DNSSEC key cache updates."
	::= { ltmDnsCacheStatEntry 28 }

ltmDnsCacheStatKeyEvictions OBJECT-TYPE
	SYNTAX Counter64
	MAX-ACCESS read-only
	STATUS current
	DESCRIPTION
		"The number of DNSSEC key cache evictions."
	::= { ltmDnsCacheStatEntry 29 }

ltmDnsCacheStatUdpBytesIn OBJECT-TYPE
	SYNTAX Counter64
	MAX-ACCESS read-only
	STATUS current
	DESCRIPTION
		"The number of UDP bytes received for resolution."
	::= { ltmDnsCacheStatEntry 30 }

ltmDnsCacheStatUdpBytesOut OBJECT-TYPE
	SYNTAX Counter64
	MAX-ACCESS read-only
	STATUS current
	DESCRIPTION
		"The number of UDP bytes sent for resolution."
	::= { ltmDnsCacheStatEntry 31 }

ltmDnsCacheStatUdpPktsIn OBJECT-TYPE
	SYNTAX Counter64
	MAX-ACCESS read-only
	STATUS current
	DESCRIPTION
		"The number of UDP packets received for resolution."
	::= { ltmDnsCacheStatEntry 32 }

ltmDnsCacheStatUdpPktsOut OBJECT-TYPE
	SYNTAX Counter64
	MAX-ACCESS read-only
	STATUS current
	DESCRIPTION
		"The number of UDP packets sent for resolution."
	::= { ltmDnsCacheStatEntry 33 }

ltmDnsCacheStatUdpCurConns OBJECT-TYPE
	SYNTAX Counter64
	MAX-ACCESS read-only
	STATUS current
	DESCRIPTION
		"The number of current UDP connections for resolution."
	::= { ltmDnsCacheStatEntry 34 }

ltmDnsCacheStatUdpMaxConns OBJECT-TYPE
	SYNTAX Counter64
	MAX-ACCESS read-only
	STATUS current
	DESCRIPTION
		"The number of maximum UDP connections for resolution."
	::= { ltmDnsCacheStatEntry 35 }

ltmDnsCacheStatUdpTotConns OBJECT-TYPE
	SYNTAX Counter64
	MAX-ACCESS read-only
	STATUS current
	DESCRIPTION
		"The total number of UDP connections for resolution."
	::= { ltmDnsCacheStatEntry 36 }

ltmDnsCacheStatTcpBytesIn OBJECT-TYPE
	SYNTAX Counter64
	MAX-ACCESS read-only
	STATUS current
	DESCRIPTION
		"The number of TCP bytes received for resolution."
	::= { ltmDnsCacheStatEntry 37 }

ltmDnsCacheStatTcpBytesOut OBJECT-TYPE
	SYNTAX Counter64
	MAX-ACCESS read-only
	STATUS current
	DESCRIPTION
		"The number of TCP bytes sent for resolution."
	::= { ltmDnsCacheStatEntry 38 }

ltmDnsCacheStatTcpPktsIn OBJECT-TYPE
	SYNTAX Counter64
	MAX-ACCESS read-only
	STATUS current
	DESCRIPTION
		"The number of TCP packets received for resolution."
	::= { ltmDnsCacheStatEntry 39 }

ltmDnsCacheStatTcpPktsOut OBJECT-TYPE
	SYNTAX Counter64
	MAX-ACCESS read-only
	STATUS current
	DESCRIPTION
		"The number of TCP packets sent for resolution."
	::= { ltmDnsCacheStatEntry 40 }

ltmDnsCacheStatTcpCurConns OBJECT-TYPE
	SYNTAX Counter64
	MAX-ACCESS read-only
	STATUS current
	DESCRIPTION
		"The number of current TCP connections for resolution."
	::= { ltmDnsCacheStatEntry 41 }

ltmDnsCacheStatTcpMaxConns OBJECT-TYPE
	SYNTAX Counter64
	MAX-ACCESS read-only
	STATUS current
	DESCRIPTION
		"The number of maximum TCP connections for resolution."
	::= { ltmDnsCacheStatEntry 42 }

ltmDnsCacheStatTcpTotConns OBJECT-TYPE
	SYNTAX Counter64
	MAX-ACCESS read-only
	STATUS current
	DESCRIPTION
		"The total number of TCP connections for resolution."
	::= { ltmDnsCacheStatEntry 43 }

ltmDnsCacheStatUnsolicitedReplies OBJECT-TYPE
	SYNTAX Counter64
	MAX-ACCESS read-only
	STATUS current
	DESCRIPTION
		"The total number of replies received to queries that were
		never sent."
	::= { ltmDnsCacheStatEntry 44 }

ltmDnsCacheStatSecUnchecked OBJECT-TYPE
	SYNTAX Counter64
	MAX-ACCESS read-only
	STATUS current
	DESCRIPTION
		"The number of DNSSEC unchecked responses."
	::= { ltmDnsCacheStatEntry 45 }

ltmDnsCacheStatSecBogus OBJECT-TYPE
	SYNTAX Counter64
	MAX-ACCESS read-only
	STATUS current
	DESCRIPTION
		"The number of DNSSEC bogus responses."
	::= { ltmDnsCacheStatEntry 46 }

ltmDnsCacheStatSecIndeterminate OBJECT-TYPE
	SYNTAX Counter64
	MAX-ACCESS read-only
	STATUS current
	DESCRIPTION
		"The number of DNSSEC indeterminate responses."
	::= { ltmDnsCacheStatEntry 47 }

ltmDnsCacheStatSecInsecure OBJECT-TYPE
	SYNTAX Counter64
	MAX-ACCESS read-only
	STATUS current
	DESCRIPTION
		"The number of DNSSEC insecure responses."
	::= { ltmDnsCacheStatEntry 48 }

ltmDnsCacheStatSecSecure OBJECT-TYPE
	SYNTAX Counter64
	MAX-ACCESS read-only
	STATUS current
	DESCRIPTION
		"The number of DNSSEC secure responses."
	::= { ltmDnsCacheStatEntry 49 }

ltmDnsCacheStatFwdQueries OBJECT-TYPE
	SYNTAX Counter64
	MAX-ACCESS read-only
	STATUS current
	DESCRIPTION
		"The total number of forward queries received."
	::= { ltmDnsCacheStatEntry 50 }

ltmDnsCacheStatFwdResponses OBJECT-TYPE
	SYNTAX Counter64
	MAX-ACCESS read-only
	STATUS current
	DESCRIPTION
		"The total number of forward responses sent."
	::= { ltmDnsCacheStatEntry 51 }

ltmDnsCacheStatRpzRewrites OBJECT-TYPE
	SYNTAX Counter64
	MAX-ACCESS read-only
	STATUS current
	DESCRIPTION
		"The number of queries rewritten due to response policy."
	::= { ltmDnsCacheStatEntry 52 }

--==================================================================
-- Profile_dns_stat
--==================================================================
ltmDnsProfileStatResetStats OBJECT-TYPE
	SYNTAX INTEGER
	MAX-ACCESS read-write
	STATUS current
	DESCRIPTION
		"The action to reset resettable statistics data in ltmDnsProfileStat.
		 Setting this value to 1 will reset statistics data.
		 Note, some statistics data may not be reset including data that are incremental counters."
	::= { ltmDnsProfileStat 1 }

ltmDnsProfileStatNumber OBJECT-TYPE
	SYNTAX INTEGER
	MAX-ACCESS read-only
	STATUS current
	DESCRIPTION
		"The number of ltmDnsProfileStat entries in the table."
	::= { ltmDnsProfileStat 2 }

ltmDnsProfileStatTable OBJECT-TYPE
	SYNTAX SEQUENCE OF LtmDnsProfileStatEntry
	MAX-ACCESS not-accessible
	STATUS current
	DESCRIPTION
		"A table containing statistics information for DNS profiles."
	::= { ltmDnsProfileStat 3 }

ltmDnsProfileStatEntry OBJECT-TYPE
	SYNTAX  LtmDnsProfileStatEntry
	MAX-ACCESS not-accessible
	STATUS current
	DESCRIPTION
		"Columns in the ltmDnsProfileStat Table"
	INDEX {
		ltmDnsProfileStatName
	}
	::= { ltmDnsProfileStatTable 1 }

LtmDnsProfileStatEntry ::=
	SEQUENCE {
        	ltmDnsProfileStatName                                     LongDisplayString,
        	ltmDnsProfileStatQueries                                  Counter64,
        	ltmDnsProfileStatResponses                                Counter64,
        	ltmDnsProfileStatResponsesPerSec                          Counter64,
        	ltmDnsProfileStatToGtm                                    Counter64,
        	ltmDnsProfileStatDnsExpressReqs                           Counter64,
        	ltmDnsProfileStatDnsExpressNotifies                       Counter64,
        	ltmDnsProfileStatToCache                                  Counter64,
        	ltmDnsProfileStatToDns                                    Counter64,
        	ltmDnsProfileStatDns64Reqs                                Counter64,
        	ltmDnsProfileStatDns64Rewrites                            Counter64,
        	ltmDnsProfileStatDns64Failures                            Counter64,
        	ltmDnsProfileStatHints                                    Counter64,
        	ltmDnsProfileStatRejects                                  Counter64,
        	ltmDnsProfileStatNoErrors                                 Counter64,
        	ltmDnsProfileStatDrops                                    Counter64,
        	ltmDnsProfileStatMalformed                                Counter64,
        	ltmDnsProfileStatTclSuspends                              Counter64,
        	ltmDnsProfileStatRecursionDesired                         Counter64,
        	ltmDnsProfileStatCheckingDisabled                         Counter64,
        	ltmDnsProfileStatEdns0                                    Counter64,
        	ltmDnsProfileStatOpcodeQuery                              Counter64,
        	ltmDnsProfileStatOpcodeNotify                             Counter64,
        	ltmDnsProfileStatOpcodeUpdate                             Counter64,
        	ltmDnsProfileStatZoneIxfr                                 Counter64,
        	ltmDnsProfileStatZoneAxfr                                 Counter64,
        	ltmDnsProfileStatAuthoritativeAnswer                      Counter64,
        	ltmDnsProfileStatRecursionAvailable                       Counter64,
        	ltmDnsProfileStatAuthenticatedData                        Counter64,
        	ltmDnsProfileStatTruncated                                Counter64,
        	ltmDnsProfileStatRcodeNoerror                             Counter64,
        	ltmDnsProfileStatRcodeNxdomain                            Counter64,
        	ltmDnsProfileStatRcodeServfail                            Counter64,
        	ltmDnsProfileStatRcodeRefused                             Counter64,
        	ltmDnsProfileStatMalicious                                Counter64,
        	ltmDnsProfileStatAReqs                                    Counter64,
        	ltmDnsProfileStatAaaaReqs                                 Counter64,
        	ltmDnsProfileStatAnyReqs                                  Counter64,
        	ltmDnsProfileStatCnameReqs                                Counter64,
        	ltmDnsProfileStatMxReqs                                   Counter64,
        	ltmDnsProfileStatNsReqs                                   Counter64,
        	ltmDnsProfileStatPtrReqs                                  Counter64,
        	ltmDnsProfileStatSoaReqs                                  Counter64,
        	ltmDnsProfileStatSrvReqs                                  Counter64,
        	ltmDnsProfileStatTxtReqs                                  Counter64,
        	ltmDnsProfileStatOtherReqs                                Counter64,
        	ltmDnsProfileStatDnsEffectiveRateLimit                    Counter64,
        	ltmDnsProfileStatDnsConfiguredObjects                     Counter64,
        	ltmDnsProfileStatDnsRateRejectedRequests                  Counter64,
        	ltmDnsProfileStatGtmEffectiveRateLimit                    Counter64,
        	ltmDnsProfileStatGtmConfiguredObjects                     Counter64,
        	ltmDnsProfileStatGtmRateRejectedRequests                  Counter64,
        	ltmDnsProfileStatGtmRewrites                              Counter64,
        	ltmDnsProfileStatOpcodeOther                              Counter64,
        	ltmDnsProfileStatFastDnsQueries                           Counter64,
        	ltmDnsProfileStatFastDnsResponses                         Counter64,
        	ltmDnsProfileStatFastDnsAllowed                           Counter64,
        	ltmDnsProfileStatFastDnsDrops                             Counter64,
        	ltmDnsProfileStatFastDnsRespTc                            Counter64,
        	ltmDnsProfileStatFastDnsRespNx                            Counter64,
        	ltmDnsProfileStatFastDnsRespNe                            Counter64,
        	ltmDnsProfileStatFastDnsRespRf                            Counter64,
        	ltmDnsProfileStatHwMalformed                              Counter64,
        	ltmDnsProfileStatHwInspected                              Counter64,
        	ltmDnsProfileStatHwCacheLookups                           Counter64,
        	ltmDnsProfileStatHwCacheResponses                         Counter64,
        	ltmDnsProfileStatNaptrReqs                                Counter64,
        	ltmDnsProfileStatRcodeBadvers                             Counter64,
        	ltmDnsProfileStatFastDnsRespBvers                         Counter64
	}

ltmDnsProfileStatName OBJECT-TYPE
	SYNTAX LongDisplayString
	MAX-ACCESS read-only
	STATUS current
	DESCRIPTION
		"The name of a DNS profile."
	::= { ltmDnsProfileStatEntry 1 }

ltmDnsProfileStatQueries OBJECT-TYPE
	SYNTAX Counter64
	MAX-ACCESS read-only
	STATUS current
	DESCRIPTION
		"The total number of DNS queries."
	::= { ltmDnsProfileStatEntry 2 }

ltmDnsProfileStatResponses OBJECT-TYPE
	SYNTAX Counter64
	MAX-ACCESS read-only
	STATUS current
	DESCRIPTION
		"The total number of DNS responses."
	::= { ltmDnsProfileStatEntry 3 }

ltmDnsProfileStatResponsesPerSec OBJECT-TYPE
	SYNTAX Counter64
	MAX-ACCESS read-only
	STATUS current
	DESCRIPTION
		"The average number of DNS responses per second."
	::= { ltmDnsProfileStatEntry 4 }

ltmDnsProfileStatToGtm OBJECT-TYPE
	SYNTAX Counter64
	MAX-ACCESS read-only
	STATUS current
	DESCRIPTION
		"The number of requests sent to GTM."
	::= { ltmDnsProfileStatEntry 5 }

ltmDnsProfileStatDnsExpressReqs OBJECT-TYPE
	SYNTAX Counter64
	MAX-ACCESS read-only
	STATUS current
	DESCRIPTION
		"The number of DNS Express requests."
	::= { ltmDnsProfileStatEntry 6 }

ltmDnsProfileStatDnsExpressNotifies OBJECT-TYPE
	SYNTAX Counter64
	MAX-ACCESS read-only
	STATUS current
	DESCRIPTION
		"The number of DNS Express notifies."
	::= { ltmDnsProfileStatEntry 7 }

ltmDnsProfileStatToCache OBJECT-TYPE
	SYNTAX Counter64
	MAX-ACCESS read-only
	STATUS current
	DESCRIPTION
		"The number of requests sent to the DNS cache."
	::= { ltmDnsProfileStatEntry 8 }

ltmDnsProfileStatToDns OBJECT-TYPE
	SYNTAX Counter64
	MAX-ACCESS read-only
	STATUS current
	DESCRIPTION
		"The number of requests sent to backend DNS."
	::= { ltmDnsProfileStatEntry 9 }

ltmDnsProfileStatDns64Reqs OBJECT-TYPE
	SYNTAX Counter64
	MAX-ACCESS read-only
	STATUS current
	DESCRIPTION
		"The number of A requests the system generated and sent."
	::= { ltmDnsProfileStatEntry 10 }

ltmDnsProfileStatDns64Rewrites OBJECT-TYPE
	SYNTAX Counter64
	MAX-ACCESS read-only
	STATUS current
	DESCRIPTION
		"The number of A responses translated to AAAA."
	::= { ltmDnsProfileStatEntry 11 }

ltmDnsProfileStatDns64Failures OBJECT-TYPE
	SYNTAX Counter64
	MAX-ACCESS read-only
	STATUS current
	DESCRIPTION
		"The number of unsuccessful AAAA requests."
	::= { ltmDnsProfileStatEntry 12 }

ltmDnsProfileStatHints OBJECT-TYPE
	SYNTAX Counter64
	MAX-ACCESS read-only
	STATUS current
	DESCRIPTION
		"The number of hint (Root Nameservers) responses sent."
	::= { ltmDnsProfileStatEntry 13 }

ltmDnsProfileStatRejects OBJECT-TYPE
	SYNTAX Counter64
	MAX-ACCESS read-only
	STATUS current
	DESCRIPTION
		"The number of reject (REFUSED) responses sent."
	::= { ltmDnsProfileStatEntry 14 }

ltmDnsProfileStatNoErrors OBJECT-TYPE
	SYNTAX Counter64
	MAX-ACCESS read-only
	STATUS current
	DESCRIPTION
		"The number of NOERROR responses sent."
	::= { ltmDnsProfileStatEntry 15 }

ltmDnsProfileStatDrops OBJECT-TYPE
	SYNTAX Counter64
	MAX-ACCESS read-only
	STATUS current
	DESCRIPTION
		"The number of packets dropped (not sent to GTM, DNS-Express, DNSSEC,
		DNS64, or Backend DNS (e.g. BIND))."
	::= { ltmDnsProfileStatEntry 16 }

ltmDnsProfileStatMalformed OBJECT-TYPE
	SYNTAX Counter64
	MAX-ACCESS read-only
	STATUS current
	DESCRIPTION
		"The number of malformed packets received."
	::= { ltmDnsProfileStatEntry 17 }

ltmDnsProfileStatTclSuspends OBJECT-TYPE
	SYNTAX Counter64
	MAX-ACCESS read-only
	STATUS current
	DESCRIPTION
		"The number of TCL suspends."
	::= { ltmDnsProfileStatEntry 18 }

ltmDnsProfileStatRecursionDesired OBJECT-TYPE
	SYNTAX Counter64
	MAX-ACCESS read-only
	STATUS current
	DESCRIPTION
		"The number of queries with RD bit set."
	::= { ltmDnsProfileStatEntry 19 }

ltmDnsProfileStatCheckingDisabled OBJECT-TYPE
	SYNTAX Counter64
	MAX-ACCESS read-only
	STATUS current
	DESCRIPTION
		"The number of queries with CD bit set."
	::= { ltmDnsProfileStatEntry 20 }

ltmDnsProfileStatEdns0 OBJECT-TYPE
	SYNTAX Counter64
	MAX-ACCESS read-only
	STATUS current
	DESCRIPTION
		"The number of queries with EDNS0 bit set."
	::= { ltmDnsProfileStatEntry 21 }

ltmDnsProfileStatOpcodeQuery OBJECT-TYPE
	SYNTAX Counter64
	MAX-ACCESS read-only
	STATUS current
	DESCRIPTION
		"The number of queries whose operation code is QUERY."
	::= { ltmDnsProfileStatEntry 22 }

ltmDnsProfileStatOpcodeNotify OBJECT-TYPE
	SYNTAX Counter64
	MAX-ACCESS read-only
	STATUS current
	DESCRIPTION
		"The number of queries whose operation code is NOTIFY."
	::= { ltmDnsProfileStatEntry 23 }

ltmDnsProfileStatOpcodeUpdate OBJECT-TYPE
	SYNTAX Counter64
	MAX-ACCESS read-only
	STATUS current
	DESCRIPTION
		"The number of queries whose operation code is UPDATE."
	::= { ltmDnsProfileStatEntry 24 }

ltmDnsProfileStatZoneIxfr OBJECT-TYPE
	SYNTAX Counter64
	MAX-ACCESS read-only
	STATUS current
	DESCRIPTION
		"The number of queries whose question type is IXFR."
	::= { ltmDnsProfileStatEntry 25 }

ltmDnsProfileStatZoneAxfr OBJECT-TYPE
	SYNTAX Counter64
	MAX-ACCESS read-only
	STATUS current
	DESCRIPTION
		"The number of queries whose question type is AXFR."
	::= { ltmDnsProfileStatEntry 26 }

ltmDnsProfileStatAuthoritativeAnswer OBJECT-TYPE
	SYNTAX Counter64
	MAX-ACCESS read-only
	STATUS current
	DESCRIPTION
		"The number of responses with AA bit set."
	::= { ltmDnsProfileStatEntry 27 }

ltmDnsProfileStatRecursionAvailable OBJECT-TYPE
	SYNTAX Counter64
	MAX-ACCESS read-only
	STATUS current
	DESCRIPTION
		"The number of responses with RA bit set."
	::= { ltmDnsProfileStatEntry 28 }

ltmDnsProfileStatAuthenticatedData OBJECT-TYPE
	SYNTAX Counter64
	MAX-ACCESS read-only
	STATUS current
	DESCRIPTION
		"The number of responses with AD bit set."
	::= { ltmDnsProfileStatEntry 29 }

ltmDnsProfileStatTruncated OBJECT-TYPE
	SYNTAX Counter64
	MAX-ACCESS read-only
	STATUS current
	DESCRIPTION
		"The number of responses with TC bit set."
	::= { ltmDnsProfileStatEntry 30 }

ltmDnsProfileStatRcodeNoerror OBJECT-TYPE
	SYNTAX Counter64
	MAX-ACCESS read-only
	STATUS current
	DESCRIPTION
		"The number of responses whose return code is NOERROR."
	::= { ltmDnsProfileStatEntry 31 }

ltmDnsProfileStatRcodeNxdomain OBJECT-TYPE
	SYNTAX Counter64
	MAX-ACCESS read-only
	STATUS current
	DESCRIPTION
		"The number of responses whose return code is NXDOMAIN."
	::= { ltmDnsProfileStatEntry 32 }

ltmDnsProfileStatRcodeServfail OBJECT-TYPE
	SYNTAX Counter64
	MAX-ACCESS read-only
	STATUS current
	DESCRIPTION
		"The number of responses whose return code is SERVFAIL."
	::= { ltmDnsProfileStatEntry 33 }

ltmDnsProfileStatRcodeRefused OBJECT-TYPE
	SYNTAX Counter64
	MAX-ACCESS read-only
	STATUS current
	DESCRIPTION
		"The number of responses whose return code is REFUSED."
	::= { ltmDnsProfileStatEntry 34 }

ltmDnsProfileStatMalicious OBJECT-TYPE
	SYNTAX Counter64
	MAX-ACCESS read-only
	STATUS current
	DESCRIPTION
		"The number of malicious packets received."
	::= { ltmDnsProfileStatEntry 35 }

ltmDnsProfileStatAReqs OBJECT-TYPE
	SYNTAX Counter64
	MAX-ACCESS read-only
	STATUS current
	DESCRIPTION
		"The number of A query packets received."
	::= { ltmDnsProfileStatEntry 36 }

ltmDnsProfileStatAaaaReqs OBJECT-TYPE
	SYNTAX Counter64
	MAX-ACCESS read-only
	STATUS current
	DESCRIPTION
		"The number of AAAA query packets received."
	::= { ltmDnsProfileStatEntry 37 }

ltmDnsProfileStatAnyReqs OBJECT-TYPE
	SYNTAX Counter64
	MAX-ACCESS read-only
	STATUS current
	DESCRIPTION
		"The number of ANY type query packets received."
	::= { ltmDnsProfileStatEntry 38 }

ltmDnsProfileStatCnameReqs OBJECT-TYPE
	SYNTAX Counter64
	MAX-ACCESS read-only
	STATUS current
	DESCRIPTION
		"The number of CNAME query packets received."
	::= { ltmDnsProfileStatEntry 39 }

ltmDnsProfileStatMxReqs OBJECT-TYPE
	SYNTAX Counter64
	MAX-ACCESS read-only
	STATUS current
	DESCRIPTION
		"The number of MX query packets received."
	::= { ltmDnsProfileStatEntry 40 }

ltmDnsProfileStatNsReqs OBJECT-TYPE
	SYNTAX Counter64
	MAX-ACCESS read-only
	STATUS current
	DESCRIPTION
		"The number of NS query packets received."
	::= { ltmDnsProfileStatEntry 41 }

ltmDnsProfileStatPtrReqs OBJECT-TYPE
	SYNTAX Counter64
	MAX-ACCESS read-only
	STATUS current
	DESCRIPTION
		"The number of PTR query packets received."
	::= { ltmDnsProfileStatEntry 42 }

ltmDnsProfileStatSoaReqs OBJECT-TYPE
	SYNTAX Counter64
	MAX-ACCESS read-only
	STATUS current
	DESCRIPTION
		"The number of SOA query packets received."
	::= { ltmDnsProfileStatEntry 43 }

ltmDnsProfileStatSrvReqs OBJECT-TYPE
	SYNTAX Counter64
	MAX-ACCESS read-only
	STATUS current
	DESCRIPTION
		"The number of SRV query packets received."
	::= { ltmDnsProfileStatEntry 44 }

ltmDnsProfileStatTxtReqs OBJECT-TYPE
	SYNTAX Counter64
	MAX-ACCESS read-only
	STATUS current
	DESCRIPTION
		"The number of TXT query packets received."
	::= { ltmDnsProfileStatEntry 45 }

ltmDnsProfileStatOtherReqs OBJECT-TYPE
	SYNTAX Counter64
	MAX-ACCESS read-only
	STATUS current
	DESCRIPTION
		"The number of uncategorized DNS packets received."
	::= { ltmDnsProfileStatEntry 46 }

ltmDnsProfileStatDnsEffectiveRateLimit OBJECT-TYPE
	SYNTAX Counter64
	MAX-ACCESS read-only
	STATUS current
	DESCRIPTION
		"The DNS services effective request rate limit."
	::= { ltmDnsProfileStatEntry 47 }

ltmDnsProfileStatDnsConfiguredObjects OBJECT-TYPE
	SYNTAX Counter64
	MAX-ACCESS read-only
	STATUS	 deprecated
	DESCRIPTION
		"Deprecated!
		DNS services objects are no longer counted, nor does the number of
		DNS services configured objects affect the licensed rate."
	::= { ltmDnsProfileStatEntry 48 }

ltmDnsProfileStatDnsRateRejectedRequests OBJECT-TYPE
	SYNTAX Counter64
	MAX-ACCESS read-only
	STATUS current
	DESCRIPTION
		"The number of DNS services requests rejected due to rate limiter action."
	::= { ltmDnsProfileStatEntry 49 }

ltmDnsProfileStatGtmEffectiveRateLimit OBJECT-TYPE
	SYNTAX Counter64
	MAX-ACCESS read-only
	STATUS	 deprecated
	DESCRIPTION
		"Deprecated!
		The GTM request rate no longer has its own licensed limit."
	::= { ltmDnsProfileStatEntry 50 }

ltmDnsProfileStatGtmConfiguredObjects OBJECT-TYPE
	SYNTAX Counter64
	MAX-ACCESS read-only
	STATUS	 deprecated
	DESCRIPTION
		"Deprecated!
		GTM services objects are no longer counted, nor does the number of
		GTM services configured objects affect the licensed rate."
	::= { ltmDnsProfileStatEntry 51 }

ltmDnsProfileStatGtmRateRejectedRequests OBJECT-TYPE
	SYNTAX Counter64
	MAX-ACCESS read-only
	STATUS	 deprecated
	DESCRIPTION
		"Deprecated!
		The GTM request rate no longer has its own licensed limit."
	::= { ltmDnsProfileStatEntry 52 }

ltmDnsProfileStatGtmRewrites OBJECT-TYPE
	SYNTAX Counter64
	MAX-ACCESS read-only
	STATUS current
	DESCRIPTION
		"The number of responses modified by GTM."
	::= { ltmDnsProfileStatEntry 53 }

ltmDnsProfileStatOpcodeOther OBJECT-TYPE
	SYNTAX Counter64
	MAX-ACCESS read-only
	STATUS current
	DESCRIPTION
		"The number of queries whose operation code is uncategorized."
	::= { ltmDnsProfileStatEntry 54 }

ltmDnsProfileStatFastDnsQueries OBJECT-TYPE
	SYNTAX Counter64
	MAX-ACCESS read-only
	STATUS current
	DESCRIPTION
		"The number of queries handled by DNS Rapid Response."
	::= { ltmDnsProfileStatEntry 55 }

ltmDnsProfileStatFastDnsResponses OBJECT-TYPE
	SYNTAX Counter64
	MAX-ACCESS read-only
	STATUS current
	DESCRIPTION
		"The number of responses returned by DNS Rapid Response."
	::= { ltmDnsProfileStatEntry 56 }

ltmDnsProfileStatFastDnsAllowed OBJECT-TYPE
	SYNTAX Counter64
	MAX-ACCESS read-only
	STATUS current
	DESCRIPTION
		"The number of non-matched queries passing through DNS Rapid Response."
	::= { ltmDnsProfileStatEntry 57 }

ltmDnsProfileStatFastDnsDrops OBJECT-TYPE
	SYNTAX Counter64
	MAX-ACCESS read-only
	STATUS current
	DESCRIPTION
		"The number of non-matching queries dropped by DNS Rapid Response."
	::= { ltmDnsProfileStatEntry 58 }

ltmDnsProfileStatFastDnsRespTc OBJECT-TYPE
	SYNTAX Counter64
	MAX-ACCESS read-only
	STATUS current
	DESCRIPTION
		"The number of non-matching queries resulting in a truncated response by DNS Rapid Response."
	::= { ltmDnsProfileStatEntry 59 }

ltmDnsProfileStatFastDnsRespNx OBJECT-TYPE
	SYNTAX Counter64
	MAX-ACCESS read-only
	STATUS current
	DESCRIPTION
		"The number of non-matching queries resulting in a NXDOMAIN response by DNS Rapid Response."
	::= { ltmDnsProfileStatEntry 60 }

ltmDnsProfileStatFastDnsRespNe OBJECT-TYPE
	SYNTAX Counter64
	MAX-ACCESS read-only
	STATUS current
	DESCRIPTION
		"The number of non-matching queries resulting in a No-Data response by DNS Rapid Response."
	::= { ltmDnsProfileStatEntry 61 }

ltmDnsProfileStatFastDnsRespRf OBJECT-TYPE
	SYNTAX Counter64
	MAX-ACCESS read-only
	STATUS current
	DESCRIPTION
		"The number of non-matching queries resulting in a REFUSED response by DNS Rapid Response."
	::= { ltmDnsProfileStatEntry 62 }

ltmDnsProfileStatHwMalformed OBJECT-TYPE
	SYNTAX Counter64
	MAX-ACCESS read-only
	STATUS current
	DESCRIPTION
		"The number of DNS queries determined to be malformed by hardware."
	::= { ltmDnsProfileStatEntry 63 }

ltmDnsProfileStatHwInspected OBJECT-TYPE
	SYNTAX Counter64
	MAX-ACCESS read-only
	STATUS current
	DESCRIPTION
		"The number of DNS queries inspected by hardware."
	::= { ltmDnsProfileStatEntry 64 }

ltmDnsProfileStatHwCacheLookups OBJECT-TYPE
	SYNTAX Counter64
	MAX-ACCESS read-only
	STATUS current
	DESCRIPTION
		"The number of DNS query match attempts in the hardware response cache."
	::= { ltmDnsProfileStatEntry 65 }

ltmDnsProfileStatHwCacheResponses OBJECT-TYPE
	SYNTAX Counter64
	MAX-ACCESS read-only
	STATUS current
	DESCRIPTION
		"The number of DNS responses returned from hardware response cache"
	::= { ltmDnsProfileStatEntry 66 }

ltmDnsProfileStatNaptrReqs OBJECT-TYPE
	SYNTAX Counter64
	MAX-ACCESS read-only
	STATUS current
	DESCRIPTION
		"The number of NAPTR query packets received."
	::= { ltmDnsProfileStatEntry 67 }

ltmDnsProfileStatRcodeBadvers OBJECT-TYPE
	SYNTAX Counter64
	MAX-ACCESS read-only
	STATUS current
	DESCRIPTION
		"The number of responses whose return code is BADVERS."
	::= { ltmDnsProfileStatEntry 68 }

ltmDnsProfileStatFastDnsRespBvers OBJECT-TYPE
	SYNTAX Counter64
	MAX-ACCESS read-only
	STATUS current
	DESCRIPTION
		"The number of queries resulting in a BADVERS response by DNS Rapid Response."
	::= { ltmDnsProfileStatEntry 69 }

--==================================================================
-- Profile_dos
--==================================================================
ltmDosProfileNumber OBJECT-TYPE
	SYNTAX INTEGER
	MAX-ACCESS read-only
	STATUS current
	DESCRIPTION
		"The number of ltmDosProfile entries in the table."
	::= { ltmDosProfile 1 }

ltmDosProfileTable OBJECT-TYPE
	SYNTAX SEQUENCE OF LtmDosProfileEntry
	MAX-ACCESS not-accessible
	STATUS current
	DESCRIPTION
		"A table containing information of DoS profile."
	::= { ltmDosProfile 2 }

ltmDosProfileEntry OBJECT-TYPE
	SYNTAX  LtmDosProfileEntry
	MAX-ACCESS not-accessible
	STATUS current
	DESCRIPTION
		"Columns in the ltmDosProfile Table"
	INDEX {
		ltmDosProfileName
	}
	::= { ltmDosProfileTable 1 }

LtmDosProfileEntry ::=
	SEQUENCE {
        	ltmDosProfileName                                         LongDisplayString,
        	ltmDosProfileConfigSource                                 INTEGER,
        	ltmDosProfileDefaultName                                  LongDisplayString
	}

ltmDosProfileName OBJECT-TYPE
	SYNTAX LongDisplayString
	MAX-ACCESS read-only
	STATUS current
	DESCRIPTION
		"The name of a DoS profile."
	::= { ltmDosProfileEntry 1 }

ltmDosProfileConfigSource OBJECT-TYPE
	SYNTAX INTEGER {
		usercfg(0),
		basecfg(1)
	}
	MAX-ACCESS read-only
	STATUS current
	DESCRIPTION
		"The state that specifies whether this is a base/pre-configured profile
		or user defined profile."
	::= { ltmDosProfileEntry 2 }

ltmDosProfileDefaultName OBJECT-TYPE
	SYNTAX LongDisplayString
	MAX-ACCESS read-only
	STATUS current
	DESCRIPTION
		"The name of the profile from which the specified profile derives
		its attribute default values."
	::= { ltmDosProfileEntry 3 }

--==================================================================
-- Dos_application
--==================================================================
ltmDosApplicationNumber OBJECT-TYPE
	SYNTAX INTEGER
	MAX-ACCESS read-only
	STATUS current
	DESCRIPTION
		"The number of ltmDosApplication entries in the table."
	::= { ltmDosApplication 1 }

ltmDosApplicationTable OBJECT-TYPE
	SYNTAX SEQUENCE OF LtmDosApplicationEntry
	MAX-ACCESS not-accessible
	STATUS current
	DESCRIPTION
		"A table containing information of DoS profile Application Security."
	::= { ltmDosApplication 2 }

ltmDosApplicationEntry OBJECT-TYPE
	SYNTAX  LtmDosApplicationEntry
	MAX-ACCESS not-accessible
	STATUS current
	DESCRIPTION
		"Columns in the ltmDosApplication Table"
	INDEX {
		ltmDosApplicationProfileName,
		ltmDosApplicationName
	}
	::= { ltmDosApplicationTable 1 }

LtmDosApplicationEntry ::=
	SEQUENCE {
        	ltmDosApplicationProfileName                              LongDisplayString,
        	ltmDosApplicationName                                     LongDisplayString,
        	ltmDosApplicationTriggerIrule                             INTEGER,
        	ltmDosApplicationTpsBasedMode                             INTEGER,
        	ltmDosApplicationLatencyBasedMode                         INTEGER,
        	ltmDosApplicationTpsBasedIpClientSideDefense              INTEGER,
        	ltmDosApplicationTpsBasedUrlClientSideDefense             INTEGER,
        	ltmDosApplicationTpsBasedIpRateLimiting                   INTEGER,
        	ltmDosApplicationTpsBasedUrlRateLimiting                  INTEGER,
        	ltmDosApplicationTpsBasedIpTpsIncreaseRate                Gauge,
        	ltmDosApplicationTpsBasedIpMaximumTps                     Gauge,
        	ltmDosApplicationTpsBasedIpMinimumTps                     Gauge,
        	ltmDosApplicationTpsBasedUrlTpsIncreaseRate               Gauge,
        	ltmDosApplicationTpsBasedUrlMaximumTps                    Gauge,
        	ltmDosApplicationTpsBasedUrlMinimumTps                    Gauge,
        	ltmDosApplicationTpsBasedMaximumPreventionDuration        Gauge,
        	ltmDosApplicationLatencyIncreaseRate                      Gauge,
        	ltmDosApplicationMaximumLatency                           Gauge,
        	ltmDosApplicationMinimumLatency                           Gauge,
        	ltmDosApplicationLatencyBasedIpClientSideDefense          INTEGER,
        	ltmDosApplicationLatencyBasedUrlClientSideDefense         INTEGER,
        	ltmDosApplicationLatencyBasedIpRateLimiting               INTEGER,
        	ltmDosApplicationLatencyBasedUrlRateLimiting              INTEGER,
        	ltmDosApplicationLatencyBasedIpTpsIncreaseRate            Gauge,
        	ltmDosApplicationLatencyBasedIpMaximumTps                 Gauge,
        	ltmDosApplicationLatencyBasedIpMinimumTps                 Gauge,
        	ltmDosApplicationLatencyBasedUrlTpsIncreaseRate           Gauge,
        	ltmDosApplicationLatencyBasedUrlMaximumTps                Gauge,
        	ltmDosApplicationLatencyBasedUrlMinimumTps                Gauge,
        	ltmDosApplicationLatencyBasedMaximumPreventionDuration    Gauge,
        	ltmDosApplicationTpsBasedSiteClientSideDefense            INTEGER,
        	ltmDosApplicationTpsBasedSiteRateLimiting                 INTEGER,
        	ltmDosApplicationTpsBasedSiteTpsIncreaseRate              Gauge,
        	ltmDosApplicationTpsBasedSiteMaximumTps                   Gauge,
        	ltmDosApplicationTpsBasedSiteMinimumTps                   Gauge,
        	ltmDosApplicationTpsBasedEscalationPeriod                 Gauge,
        	ltmDosApplicationTpsBasedDeEscalationPeriod               Gauge,
        	ltmDosApplicationLatencyBasedSiteClientSideDefense        INTEGER,
        	ltmDosApplicationLatencyBasedSiteRateLimiting             INTEGER,
        	ltmDosApplicationLatencyBasedSiteTpsIncreaseRate          Gauge,
        	ltmDosApplicationLatencyBasedSiteMaximumTps               Gauge,
        	ltmDosApplicationLatencyBasedSiteMinimumTps               Gauge,
        	ltmDosApplicationLatencyBasedEscalationPeriod             Gauge,
        	ltmDosApplicationLatencyBasedDeEscalationPeriod           Gauge,
        	ltmDosApplicationHeavyUrlProtection                       INTEGER,
        	ltmDosApplicationHeavyUrlAutomaticDetection               INTEGER,
        	ltmDosApplicationHeavyUrlLatencyThreshold                 Gauge
	}

ltmDosApplicationProfileName OBJECT-TYPE
	SYNTAX LongDisplayString
	MAX-ACCESS read-only
	STATUS current
	DESCRIPTION
		"The name of a DoS profile."
	::= { ltmDosApplicationEntry 1 }

ltmDosApplicationName OBJECT-TYPE
	SYNTAX LongDisplayString
	MAX-ACCESS read-only
	STATUS current
	DESCRIPTION
		"The dummy name of enabled Application Security on this profile."
	::= { ltmDosApplicationEntry 2 }

ltmDosApplicationTriggerIrule OBJECT-TYPE
	SYNTAX INTEGER {
		false(0),
		true(1)
	}
	MAX-ACCESS read-only
	STATUS current
	DESCRIPTION
		"The state indicating whether Application DoS iRule event is triggered or not."
	::= { ltmDosApplicationEntry 3 }

ltmDosApplicationTpsBasedMode OBJECT-TYPE
	SYNTAX INTEGER {
		off(0),
		transparent(1),
		blocking(2)
	}
	MAX-ACCESS read-only
	STATUS current
	DESCRIPTION
		"The operation mode of TPS-based anomaly detection ."
	::= { ltmDosApplicationEntry 4 }

ltmDosApplicationLatencyBasedMode OBJECT-TYPE
	SYNTAX INTEGER {
		off(0),
		transparent(1),
		blocking(2)
	}
	MAX-ACCESS read-only
	STATUS current
	DESCRIPTION
		"The operation mode of Latency-based anomaly detection."
	::= { ltmDosApplicationEntry 5 }

ltmDosApplicationTpsBasedIpClientSideDefense OBJECT-TYPE
	SYNTAX INTEGER {
		false(0),
		true(1)
	}
	MAX-ACCESS read-only
	STATUS current
	DESCRIPTION
		"The state indicating whether Source IP-based client side integrity defense in TPS-based anomaly is enabled or not."
	::= { ltmDosApplicationEntry 6 }

ltmDosApplicationTpsBasedUrlClientSideDefense OBJECT-TYPE
	SYNTAX INTEGER {
		false(0),
		true(1)
	}
	MAX-ACCESS read-only
	STATUS current
	DESCRIPTION
		"The state indicating whether URL-based client side integrity defense in TPS-based anomaly is enabled or not."
	::= { ltmDosApplicationEntry 7 }

ltmDosApplicationTpsBasedIpRateLimiting OBJECT-TYPE
	SYNTAX INTEGER {
		false(0),
		true(1)
	}
	MAX-ACCESS read-only
	STATUS current
	DESCRIPTION
		"The state indicating whether Source IP-based rate limiting in TPS-based anomaly is enabled or not."
	::= { ltmDosApplicationEntry 8 }

ltmDosApplicationTpsBasedUrlRateLimiting OBJECT-TYPE
	SYNTAX INTEGER {
		false(0),
		true(1)
	}
	MAX-ACCESS read-only
	STATUS current
	DESCRIPTION
		"The state indicating whether URL-based rate limiting in TPS-based anomaly is enabled or not."
	::= { ltmDosApplicationEntry 9 }

ltmDosApplicationTpsBasedIpTpsIncreaseRate OBJECT-TYPE
	SYNTAX Gauge
	MAX-ACCESS read-only
	STATUS current
	DESCRIPTION
		"The value that specifies the percentage by which TPS increased in IP detection criteria of TPS-based anomaly.
		It is only used when Source IP-based client side integrity defense and/or rate limiting are enabled in TPS-based anomaly, otherwise ignored."
	::= { ltmDosApplicationEntry 10 }

ltmDosApplicationTpsBasedIpMaximumTps OBJECT-TYPE
	SYNTAX Gauge
	MAX-ACCESS read-only
	STATUS current
	DESCRIPTION
		"The value that specifies the amount which TPS reached in IP detection criteria of TPS-based anomaly.
		It is only used when Source IP-based client side integrity defense and/or rate limiting are enabled in TPS-based anomaly, otherwise ignored."
	::= { ltmDosApplicationEntry 11 }

ltmDosApplicationTpsBasedIpMinimumTps OBJECT-TYPE
	SYNTAX Gauge
	MAX-ACCESS read-only
	STATUS current
	DESCRIPTION
		"The value that specifies the minimum TPS threshold for detection in IP detection criteria of TPS-based anomaly.
		It is only used when Source IP-based client side integrity defense and/or rate limiting are enabled in TPS-based anomaly, otherwise ignored."
	::= { ltmDosApplicationEntry 12 }

ltmDosApplicationTpsBasedUrlTpsIncreaseRate OBJECT-TYPE
	SYNTAX Gauge
	MAX-ACCESS read-only
	STATUS current
	DESCRIPTION
		"The value that specifies the percentage by which TPS increased in URL detection criteria of TPS-based anomaly.
		It is only used when URL-based client side integrity defense and/or rate limiting are enabled in TPS-based anomaly, otherwise ignored."
	::= { ltmDosApplicationEntry 13 }

ltmDosApplicationTpsBasedUrlMaximumTps OBJECT-TYPE
	SYNTAX Gauge
	MAX-ACCESS read-only
	STATUS current
	DESCRIPTION
		"The value that specifies the amount which TPS reached in URL detection criteria of TPS-based anomaly.
		It is only used when URL-based client side integrity defense and/or rate limiting are enabled in TPS-based anomaly, otherwise ignored."
	::= { ltmDosApplicationEntry 14 }

ltmDosApplicationTpsBasedUrlMinimumTps OBJECT-TYPE
	SYNTAX Gauge
	MAX-ACCESS read-only
	STATUS current
	DESCRIPTION
		"The value that specifies the minimum TPS threshold for detection in URL detection criteria of TPS-based anomaly.
		It is only used when URL-based client side integrity defense and/or rate limiting are enabled in TPS-based anomaly, otherwise ignored."
	::= { ltmDosApplicationEntry 15 }

ltmDosApplicationTpsBasedMaximumPreventionDuration OBJECT-TYPE
	SYNTAX Gauge
	MAX-ACCESS read-only
	STATUS	 deprecated
	DESCRIPTION
		"Deprecated! Replaced by ltmDosApplicationTpsBasedEscalationPeriod and ltmDosApplicationTpsBasedDeescalationPeriod.
		The value that specifies the maximum prevention duration (in seconds) in TPS-based anomaly. 0 for unlimited."
	::= { ltmDosApplicationEntry 16 }

ltmDosApplicationLatencyIncreaseRate OBJECT-TYPE
	SYNTAX Gauge
	MAX-ACCESS read-only
	STATUS current
	DESCRIPTION
		"The value that specifies the percentage by which latency increased in detection criteria of Latency-based anomaly."
	::= { ltmDosApplicationEntry 17 }

ltmDosApplicationMaximumLatency OBJECT-TYPE
	SYNTAX Gauge
	MAX-ACCESS read-only
	STATUS current
	DESCRIPTION
		"The value that specifies the amount which latency reached (in milliseconds) in detection criteria of Latency-based anomaly."
	::= { ltmDosApplicationEntry 18 }

ltmDosApplicationMinimumLatency OBJECT-TYPE
	SYNTAX Gauge
	MAX-ACCESS read-only
	STATUS current
	DESCRIPTION
		"The value that specifies the minimum latency threshold for detection (in milliseconds) in detection criteria of Latency-based anomaly."
	::= { ltmDosApplicationEntry 19 }

ltmDosApplicationLatencyBasedIpClientSideDefense OBJECT-TYPE
	SYNTAX INTEGER {
		false(0),
		true(1)
	}
	MAX-ACCESS read-only
	STATUS current
	DESCRIPTION
		"The state indicating whether Source IP-based client side integrity defense in Latency-based anomaly is enabled or not."
	::= { ltmDosApplicationEntry 20 }

ltmDosApplicationLatencyBasedUrlClientSideDefense OBJECT-TYPE
	SYNTAX INTEGER {
		false(0),
		true(1)
	}
	MAX-ACCESS read-only
	STATUS current
	DESCRIPTION
		"The state indicating whether URL-based client side integrity defense in Latency-based anomaly is enabled or not."
	::= { ltmDosApplicationEntry 21 }

ltmDosApplicationLatencyBasedIpRateLimiting OBJECT-TYPE
	SYNTAX INTEGER {
		false(0),
		true(1)
	}
	MAX-ACCESS read-only
	STATUS current
	DESCRIPTION
		"The state indicating whether Source IP-based rate limiting in Latency-based anomaly is enabled or not."
	::= { ltmDosApplicationEntry 22 }

ltmDosApplicationLatencyBasedUrlRateLimiting OBJECT-TYPE
	SYNTAX INTEGER {
		false(0),
		true(1)
	}
	MAX-ACCESS read-only
	STATUS current
	DESCRIPTION
		"The state indicating whether URL-based rate limiting in Latency-based anomaly is enabled or not."
	::= { ltmDosApplicationEntry 23 }

ltmDosApplicationLatencyBasedIpTpsIncreaseRate OBJECT-TYPE
	SYNTAX Gauge
	MAX-ACCESS read-only
	STATUS current
	DESCRIPTION
		"The value that specifies the percentage by which TPS increased in suspicious IP criteria of Latency-based anomaly.
		It is only used when Source IP-based client side integrity defense and/or rate limiting are enabled in Latency-based anomaly, otherwise ignored."
	::= { ltmDosApplicationEntry 24 }

ltmDosApplicationLatencyBasedIpMaximumTps OBJECT-TYPE
	SYNTAX Gauge
	MAX-ACCESS read-only
	STATUS current
	DESCRIPTION
		"The value that specifies the amount which TPS reached in suspicious IP criteria of Latency-based anomaly.
		It is only used when Source IP-based client side integrity defense and/or rate limiting are enabled in Latency-based anomaly, otherwise ignored."
	::= { ltmDosApplicationEntry 25 }

ltmDosApplicationLatencyBasedIpMinimumTps OBJECT-TYPE
	SYNTAX Gauge
	MAX-ACCESS read-only
	STATUS current
	DESCRIPTION
		"The value that specifies the minimum TPS threshold for detection in suspicious IP criteria of Latency-based anomaly.
		It is only used when Source IP-based client side integrity defense and/or rate limiting are enabled in Latency-based anomaly, otherwise ignored."
	::= { ltmDosApplicationEntry 26 }

ltmDosApplicationLatencyBasedUrlTpsIncreaseRate OBJECT-TYPE
	SYNTAX Gauge
	MAX-ACCESS read-only
	STATUS current
	DESCRIPTION
		"The value that specifies the percentage by which TPS increased in suspicious URL criteria of Latency-based anomaly.
		It is only used when URL-based client side integrity defense and/or rate limiting are enabled in Latency-based anomaly, otherwise ignored."
	::= { ltmDosApplicationEntry 27 }

ltmDosApplicationLatencyBasedUrlMaximumTps OBJECT-TYPE
	SYNTAX Gauge
	MAX-ACCESS read-only
	STATUS current
	DESCRIPTION
		"The value that specifies the amount which TPS reached in suspicious URL criteria of Latency-based anomaly.
		It is only used when URL-based client side integrity defense and/or rate limiting are enabled in Latency-based anomaly, otherwise ignored."
	::= { ltmDosApplicationEntry 28 }

ltmDosApplicationLatencyBasedUrlMinimumTps OBJECT-TYPE
	SYNTAX Gauge
	MAX-ACCESS read-only
	STATUS current
	DESCRIPTION
		"The value that specifies the minimum TPS threshold for detection in suspicious URL criteria of Latency-based anomaly.
		It is only used when URL-based client side integrity defense and/or rate limiting are enabled in Latency-based anomaly, otherwise ignored."
	::= { ltmDosApplicationEntry 29 }

ltmDosApplicationLatencyBasedMaximumPreventionDuration OBJECT-TYPE
	SYNTAX Gauge
	MAX-ACCESS read-only
	STATUS	 deprecated
	DESCRIPTION
		"Deprecated! Replaced by ltmDosApplicationLatencyBasedEscalationPeriod and ltmDosApplicationLatencyBasedDeescalationPeriod.
		The value that specifies the maximum prevention duration (in seconds) in Latency-based anomaly. 0 for unlimited."
	::= { ltmDosApplicationEntry 30 }

ltmDosApplicationTpsBasedSiteClientSideDefense OBJECT-TYPE
	SYNTAX INTEGER {
		false(0),
		true(1)
	}
	MAX-ACCESS read-only
	STATUS current
	DESCRIPTION
		"The state indicating whether Site-wide client side integrity defense in TPS-based anomaly is enabled or not."
	::= { ltmDosApplicationEntry 31 }

ltmDosApplicationTpsBasedSiteRateLimiting OBJECT-TYPE
	SYNTAX INTEGER {
		false(0),
		true(1)
	}
	MAX-ACCESS read-only
	STATUS current
	DESCRIPTION
		"The state indicating whether Site-wide rate limiting in TPS-based anomaly is enabled or not."
	::= { ltmDosApplicationEntry 32 }

ltmDosApplicationTpsBasedSiteTpsIncreaseRate OBJECT-TYPE
	SYNTAX Gauge
	MAX-ACCESS read-only
	STATUS current
	DESCRIPTION
		"The value that specifies the percentage by which TPS increased in Site-wide detection criteria of TPS-based anomaly.
		It is only used when Site-wide client side integrity defense and/or rate limiting are enabled in TPS-based anomaly, otherwise ignored."
	::= { ltmDosApplicationEntry 33 }

ltmDosApplicationTpsBasedSiteMaximumTps OBJECT-TYPE
	SYNTAX Gauge
	MAX-ACCESS read-only
	STATUS current
	DESCRIPTION
		"The value that specifies the amount which TPS reached in Site-wide detection criteria of TPS-based anomaly.
		It is only used when Site-wide client side integrity defense and/or rate limiting are enabled in TPS-based anomaly, otherwise ignored."
	::= { ltmDosApplicationEntry 34 }

ltmDosApplicationTpsBasedSiteMinimumTps OBJECT-TYPE
	SYNTAX Gauge
	MAX-ACCESS read-only
	STATUS current
	DESCRIPTION
		"The value that specifies the minimum TPS threshold for detection in Site-wide detection criteria of TPS-based anomaly.
		It is only used when Site-wide client side integrity defense and/or rate limiting are enabled in TPS-based anomaly, otherwise ignored."
	::= { ltmDosApplicationEntry 35 }

ltmDosApplicationTpsBasedEscalationPeriod OBJECT-TYPE
	SYNTAX Gauge
	MAX-ACCESS read-only
	STATUS current
	DESCRIPTION
		"The value that specifies the escalation period (in seconds) in TPS-based anomaly."
	::= { ltmDosApplicationEntry 36 }

ltmDosApplicationTpsBasedDeEscalationPeriod OBJECT-TYPE
	SYNTAX Gauge
	MAX-ACCESS read-only
	STATUS current
	DESCRIPTION
		"The value that specifies the de-escalation period (in seconds) in TPS-based anomaly."
	::= { ltmDosApplicationEntry 37 }

ltmDosApplicationLatencyBasedSiteClientSideDefense OBJECT-TYPE
	SYNTAX INTEGER {
		false(0),
		true(1)
	}
	MAX-ACCESS read-only
	STATUS current
	DESCRIPTION
		"The state indicating whether Site-wide client side integrity defense in Latency-based anomaly is enabled or not."
	::= { ltmDosApplicationEntry 38 }

ltmDosApplicationLatencyBasedSiteRateLimiting OBJECT-TYPE
	SYNTAX INTEGER {
		false(0),
		true(1)
	}
	MAX-ACCESS read-only
	STATUS current
	DESCRIPTION
		"The state indicating whether Site-wide rate limiting in Latency-based anomaly is enabled or not."
	::= { ltmDosApplicationEntry 39 }

ltmDosApplicationLatencyBasedSiteTpsIncreaseRate OBJECT-TYPE
	SYNTAX Gauge
	MAX-ACCESS read-only
	STATUS current
	DESCRIPTION
		"The value that specifies the percentage by which TPS increased in suspicious Site-wide criteria of Latency-based anomaly.
		It is only used when Site-wide client side integrity defense and/or rate limiting are enabled in Latency-based anomaly, otherwise ignored."
	::= { ltmDosApplicationEntry 40 }

ltmDosApplicationLatencyBasedSiteMaximumTps OBJECT-TYPE
	SYNTAX Gauge
	MAX-ACCESS read-only
	STATUS current
	DESCRIPTION
		"The value that specifies the amount which TPS reached in suspicious Site-wide criteria of Latency-based anomaly.
		It is only used when Site-wide client side integrity defense and/or rate limiting are enabled in Latency-based anomaly, otherwise ignored."
	::= { ltmDosApplicationEntry 41 }

ltmDosApplicationLatencyBasedSiteMinimumTps OBJECT-TYPE
	SYNTAX Gauge
	MAX-ACCESS read-only
	STATUS current
	DESCRIPTION
		"The value that specifies the minimum TPS threshold for detection in suspicious Site-wide criteria of Latency-based anomaly.
		It is only used when Site-wide client side integrity defense and/or rate limiting are enabled in Latency-based anomaly, otherwise ignored."
	::= { ltmDosApplicationEntry 42 }

ltmDosApplicationLatencyBasedEscalationPeriod OBJECT-TYPE
	SYNTAX Gauge
	MAX-ACCESS read-only
	STATUS current
	DESCRIPTION
		"The value that specifies the escalation period (in seconds) in Latency-based anomaly."
	::= { ltmDosApplicationEntry 43 }

ltmDosApplicationLatencyBasedDeEscalationPeriod OBJECT-TYPE
	SYNTAX Gauge
	MAX-ACCESS read-only
	STATUS current
	DESCRIPTION
		"The value that specifies the de-escalation period (in seconds) in Latency-based anomaly."
	::= { ltmDosApplicationEntry 44 }

ltmDosApplicationHeavyUrlProtection OBJECT-TYPE
	SYNTAX INTEGER {
		false(0),
		true(1)
	}
	MAX-ACCESS read-only
	STATUS current
	DESCRIPTION
		"The state indicating whether heavy URL protection is enabled or not."
	::= { ltmDosApplicationEntry 45 }

ltmDosApplicationHeavyUrlAutomaticDetection OBJECT-TYPE
	SYNTAX INTEGER {
		false(0),
		true(1)
	}
	MAX-ACCESS read-only
	STATUS current
	DESCRIPTION
		"The state indicating whether automatic heavy URL detection is enabled or not."
	::= { ltmDosApplicationEntry 46 }

ltmDosApplicationHeavyUrlLatencyThreshold OBJECT-TYPE
	SYNTAX Gauge
	MAX-ACCESS read-only
	STATUS current
	DESCRIPTION
		"The value that specifies the latency threshold for automatic heavy URL detection (in milliseconds)."
	::= { ltmDosApplicationEntry 47 }

--==================================================================
-- Dos_white_ip
--==================================================================
ltmDosWhiteIpNumber OBJECT-TYPE
	SYNTAX INTEGER
	MAX-ACCESS read-only
	STATUS current
	DESCRIPTION
		"The number of ltmDosWhiteIp entries in the table."
	::= { ltmDosWhiteIp 1 }

ltmDosWhiteIpTable OBJECT-TYPE
	SYNTAX SEQUENCE OF LtmDosWhiteIpEntry
	MAX-ACCESS not-accessible
	STATUS current
	DESCRIPTION
		"A table containing information of DoS profile Application Security IP address whitelist."
	::= { ltmDosWhiteIp 2 }

ltmDosWhiteIpEntry OBJECT-TYPE
	SYNTAX  LtmDosWhiteIpEntry
	MAX-ACCESS not-accessible
	STATUS current
	DESCRIPTION
		"Columns in the ltmDosWhiteIp Table"
	INDEX {
		ltmDosWhiteIpParentProfile,
		ltmDosWhiteIpParentName,
		ltmDosWhiteIpAddressType,
		ltmDosWhiteIpAddress,
		ltmDosWhiteIpNetmaskType,
		ltmDosWhiteIpNetmask
	}
	::= { ltmDosWhiteIpTable 1 }

LtmDosWhiteIpEntry ::=
	SEQUENCE {
        	ltmDosWhiteIpParentProfile                                LongDisplayString,
        	ltmDosWhiteIpParentName                                   LongDisplayString,
        	ltmDosWhiteIpAddressType                                  InetAddressType,
        	ltmDosWhiteIpAddress                                      InetAddress,
        	ltmDosWhiteIpNetmaskType                                  InetAddressType,
        	ltmDosWhiteIpNetmask                                      InetAddress
	}

ltmDosWhiteIpParentProfile OBJECT-TYPE
	SYNTAX LongDisplayString
	MAX-ACCESS read-only
	STATUS current
	DESCRIPTION
		"The name of a DoS profile."
	::= { ltmDosWhiteIpEntry 1 }

ltmDosWhiteIpParentName OBJECT-TYPE
	SYNTAX LongDisplayString
	MAX-ACCESS read-only
	STATUS current
	DESCRIPTION
		"The dummy name of enabled Application Security on this profile."
	::= { ltmDosWhiteIpEntry 2 }

ltmDosWhiteIpAddressType OBJECT-TYPE
	SYNTAX InetAddressType
	MAX-ACCESS read-only
	STATUS current
	DESCRIPTION
		"The IP address type of ltmDosWhiteIpAddress"
	::= { ltmDosWhiteIpEntry 3 }

ltmDosWhiteIpAddress OBJECT-TYPE
	SYNTAX InetAddress
	MAX-ACCESS read-only
	STATUS current
	DESCRIPTION
		"The IP address in the whitelist of the specified DoS profile with Application Security.
		It is interpreted within the context of a ltmDosWhiteIpAddressType value."
	::= { ltmDosWhiteIpEntry 4 }

ltmDosWhiteIpNetmaskType OBJECT-TYPE
	SYNTAX InetAddressType
	MAX-ACCESS read-only
	STATUS current
	DESCRIPTION
		"The IP address type of ltmDosWhiteIpNetmask"
	::= { ltmDosWhiteIpEntry 5 }

ltmDosWhiteIpNetmask OBJECT-TYPE
	SYNTAX InetAddress
	MAX-ACCESS read-only
	STATUS current
	DESCRIPTION
		"The subnet mask associated with the specified Application DoS profile whitelist IP address.
		It is interpreted within the context of a ltmDosWhiteIpNetmaskType value."
	::= { ltmDosWhiteIpEntry 6 }

--==================================================================
-- Dns_security
--==================================================================
ltmDnsSecurityNumber OBJECT-TYPE
	SYNTAX INTEGER
	MAX-ACCESS read-only
	STATUS current
	DESCRIPTION
		"The number of ltmDnsSecurity entries in the table."
	::= { ltmDnsSecurity 1 }

ltmDnsSecurityTable OBJECT-TYPE
	SYNTAX SEQUENCE OF LtmDnsSecurityEntry
	MAX-ACCESS not-accessible
	STATUS current
	DESCRIPTION
		"A table containing information of DNS security."
	::= { ltmDnsSecurity 2 }

ltmDnsSecurityEntry OBJECT-TYPE
	SYNTAX  LtmDnsSecurityEntry
	MAX-ACCESS not-accessible
	STATUS current
	DESCRIPTION
		"Columns in the ltmDnsSecurity Table"
	INDEX {
		ltmDnsSecurityName
	}
	::= { ltmDnsSecurityTable 1 }

LtmDnsSecurityEntry ::=
	SEQUENCE {
        	ltmDnsSecurityName                                        LongDisplayString,
        	ltmDnsSecurityQueryTypeInclusion                          INTEGER
	}

ltmDnsSecurityName OBJECT-TYPE
	SYNTAX LongDisplayString
	MAX-ACCESS read-only
	STATUS current
	DESCRIPTION
		"The name of DNS security profile."
	::= { ltmDnsSecurityEntry 1 }

ltmDnsSecurityQueryTypeInclusion OBJECT-TYPE
	SYNTAX INTEGER {
		no(0),
		yes(1)
	}
	MAX-ACCESS read-only
	STATUS current
	DESCRIPTION
		"The state indicating whether or not the query type filter is
	        an enable (inclusion) or a disable (exclusion) list.
	        Value 0 (no) implies disable and 1 (yes) is enable."
	::= { ltmDnsSecurityEntry 2 }

--==================================================================
-- Dns_security_stat
--==================================================================
ltmDnsSecurityStatResetStats OBJECT-TYPE
	SYNTAX INTEGER
	MAX-ACCESS read-write
	STATUS current
	DESCRIPTION
		"The action to reset resettable statistics data in ltmDnsSecurityStat.
		 Setting this value to 1 will reset statistics data.
		 Note, some statistics data may not be reset including data that are incremental counters."
	::= { ltmDnsSecurityStat 1 }

ltmDnsSecurityStatNumber OBJECT-TYPE
	SYNTAX INTEGER
	MAX-ACCESS read-only
	STATUS current
	DESCRIPTION
		"The number of ltmDnsSecurityStat entries in the table."
	::= { ltmDnsSecurityStat 2 }

ltmDnsSecurityStatTable OBJECT-TYPE
	SYNTAX SEQUENCE OF LtmDnsSecurityStatEntry
	MAX-ACCESS not-accessible
	STATUS current
	DESCRIPTION
		"A table containing statistics information of DNS security."
	::= { ltmDnsSecurityStat 3 }

ltmDnsSecurityStatEntry OBJECT-TYPE
	SYNTAX  LtmDnsSecurityStatEntry
	MAX-ACCESS not-accessible
	STATUS current
	DESCRIPTION
		"Columns in the ltmDnsSecurityStat Table"
	INDEX {
		ltmDnsSecurityStatName
	}
	::= { ltmDnsSecurityStatTable 1 }

LtmDnsSecurityStatEntry ::=
	SEQUENCE {
        	ltmDnsSecurityStatName                                    LongDisplayString,
        	ltmDnsSecurityStatFilteredDrops                           Counter64,
        	ltmDnsSecurityStatADrops                                  Counter64,
        	ltmDnsSecurityStatAaaaDrops                               Counter64,
        	ltmDnsSecurityStatAnyDrops                                Counter64,
        	ltmDnsSecurityStatCnameDrops                              Counter64,
        	ltmDnsSecurityStatMxDrops                                 Counter64,
        	ltmDnsSecurityStatNsDrops                                 Counter64,
        	ltmDnsSecurityStatPtrDrops                                Counter64,
        	ltmDnsSecurityStatSoaDrops                                Counter64,
        	ltmDnsSecurityStatSrvDrops                                Counter64,
        	ltmDnsSecurityStatTxtDrops                                Counter64,
        	ltmDnsSecurityStatOtherDrops                              Counter64
	}

ltmDnsSecurityStatName OBJECT-TYPE
	SYNTAX LongDisplayString
	MAX-ACCESS read-only
	STATUS current
	DESCRIPTION
		"The name of DNS security profile."
	::= { ltmDnsSecurityStatEntry 1 }

ltmDnsSecurityStatFilteredDrops OBJECT-TYPE
	SYNTAX Counter64
	MAX-ACCESS read-only
	STATUS current
	DESCRIPTION
		"The total number of dropped DNS packets due to filtering."
	::= { ltmDnsSecurityStatEntry 2 }

ltmDnsSecurityStatADrops OBJECT-TYPE
	SYNTAX Counter64
	MAX-ACCESS read-only
	STATUS current
	DESCRIPTION
		"The total number of dropped A packets due to filtering."
	::= { ltmDnsSecurityStatEntry 3 }

ltmDnsSecurityStatAaaaDrops OBJECT-TYPE
	SYNTAX Counter64
	MAX-ACCESS read-only
	STATUS current
	DESCRIPTION
		"The total number of dropped AAAA packets due to filtering."
	::= { ltmDnsSecurityStatEntry 4 }

ltmDnsSecurityStatAnyDrops OBJECT-TYPE
	SYNTAX Counter64
	MAX-ACCESS read-only
	STATUS current
	DESCRIPTION
		"The total number of dropped ANY packets due to filtering."
	::= { ltmDnsSecurityStatEntry 5 }

ltmDnsSecurityStatCnameDrops OBJECT-TYPE
	SYNTAX Counter64
	MAX-ACCESS read-only
	STATUS current
	DESCRIPTION
		"The total number of dropped CNAME packets due to filtering."
	::= { ltmDnsSecurityStatEntry 6 }

ltmDnsSecurityStatMxDrops OBJECT-TYPE
	SYNTAX Counter64
	MAX-ACCESS read-only
	STATUS current
	DESCRIPTION
		"The total number of dropped MX packets due to filtering."
	::= { ltmDnsSecurityStatEntry 7 }

ltmDnsSecurityStatNsDrops OBJECT-TYPE
	SYNTAX Counter64
	MAX-ACCESS read-only
	STATUS current
	DESCRIPTION
		"The total number of dropped NS packets due to filtering."
	::= { ltmDnsSecurityStatEntry 8 }

ltmDnsSecurityStatPtrDrops OBJECT-TYPE
	SYNTAX Counter64
	MAX-ACCESS read-only
	STATUS current
	DESCRIPTION
		"The total number of dropped PTR packets due to filtering."
	::= { ltmDnsSecurityStatEntry 9 }

ltmDnsSecurityStatSoaDrops OBJECT-TYPE
	SYNTAX Counter64
	MAX-ACCESS read-only
	STATUS current
	DESCRIPTION
		"The total number of dropped SOA packets due to filtering."
	::= { ltmDnsSecurityStatEntry 10 }

ltmDnsSecurityStatSrvDrops OBJECT-TYPE
	SYNTAX Counter64
	MAX-ACCESS read-only
	STATUS current
	DESCRIPTION
		"The total number of dropped SRV packets due to filtering."
	::= { ltmDnsSecurityStatEntry 11 }

ltmDnsSecurityStatTxtDrops OBJECT-TYPE
	SYNTAX Counter64
	MAX-ACCESS read-only
	STATUS current
	DESCRIPTION
		"The total number of dropped TXT packets due to filtering."
	::= { ltmDnsSecurityStatEntry 12 }

ltmDnsSecurityStatOtherDrops OBJECT-TYPE
	SYNTAX Counter64
	MAX-ACCESS read-only
	STATUS current
	DESCRIPTION
		"The total number of dropped OTHER packets due to filtering."
	::= { ltmDnsSecurityStatEntry 13 }

--==================================================================
-- Bwc_policy_stat
--==================================================================
ltmBwcPolicyStatResetStats OBJECT-TYPE
	SYNTAX INTEGER
	MAX-ACCESS read-write
	STATUS current
	DESCRIPTION
		"The action to reset resettable statistics data in ltmBwcPolicyStat.
		 Setting this value to 1 will reset statistics data.
		 Note, some statistics data may not be reset including data that are incremental counters."
	::= { ltmBwcPolicyStat 1 }

ltmBwcPolicyStatNumber OBJECT-TYPE
	SYNTAX INTEGER
	MAX-ACCESS read-only
	STATUS current
	DESCRIPTION
		"The number of ltmBwcPolicyStat entries in the table."
	::= { ltmBwcPolicyStat 2 }

ltmBwcPolicyStatTable OBJECT-TYPE
	SYNTAX SEQUENCE OF LtmBwcPolicyStatEntry
	MAX-ACCESS not-accessible
	STATUS current
	DESCRIPTION
		"A table containing statistics information of BWC policy."
	::= { ltmBwcPolicyStat 3 }

ltmBwcPolicyStatEntry OBJECT-TYPE
	SYNTAX  LtmBwcPolicyStatEntry
	MAX-ACCESS not-accessible
	STATUS current
	DESCRIPTION
		"Columns in the ltmBwcPolicyStat Table"
	INDEX {
		ltmBwcPolicyStatName
	}
	::= { ltmBwcPolicyStatTable 1 }

LtmBwcPolicyStatEntry ::=
	SEQUENCE {
        	ltmBwcPolicyStatName                                      LongDisplayString,
        	ltmBwcPolicyStatBytesPerSec                               Counter64,
        	ltmBwcPolicyStatBytesPerSecOut                            Counter64,
        	ltmBwcPolicyStatBytesIn                                   Counter64,
        	ltmBwcPolicyStatBytesPassed                               Counter64,
        	ltmBwcPolicyStatBytesDropped                              Counter64,
        	ltmBwcPolicyStatPacketsIn                                 Counter64,
        	ltmBwcPolicyStatPacketsPassed                             Counter64,
        	ltmBwcPolicyStatActivePolicies                            Counter64,
        	ltmBwcPolicyStatInactivePolicies                          Counter64,
        	ltmBwcPolicyStatTotalPolicies                             Counter64,
        	ltmBwcPolicyStatTimeDataCollected                         Counter64,
        	ltmBwcPolicyStatPacketsPerSec                             Counter64,
        	ltmBwcPolicyStatPacketsPerSecOut                          Counter64
	}

ltmBwcPolicyStatName OBJECT-TYPE
	SYNTAX LongDisplayString
	MAX-ACCESS read-only
	STATUS current
	DESCRIPTION
		"The name of BWC policy that is configured. There are many types of
	        BWC policies. This name is string upto max of string name of policy."
	::= { ltmBwcPolicyStatEntry 1 }

ltmBwcPolicyStatBytesPerSec OBJECT-TYPE
	SYNTAX Counter64
	MAX-ACCESS read-only
	STATUS current
	DESCRIPTION
		"The average input bytes/sec over last 4 seconds. These are bytes as
	        processed by this policy."
	::= { ltmBwcPolicyStatEntry 2 }

ltmBwcPolicyStatBytesPerSecOut OBJECT-TYPE
	SYNTAX Counter64
	MAX-ACCESS read-only
	STATUS current
	DESCRIPTION
		"The average output bytes/sec over last 4 seconds. These are bytes
	        processed by this policy."
	::= { ltmBwcPolicyStatEntry 3 }

ltmBwcPolicyStatBytesIn OBJECT-TYPE
	SYNTAX Counter64
	MAX-ACCESS read-only
	STATUS current
	DESCRIPTION
		"The number of bytes ingress. These are bytes ingress to policy before
	        being processed by policy."
	::= { ltmBwcPolicyStatEntry 4 }

ltmBwcPolicyStatBytesPassed OBJECT-TYPE
	SYNTAX Counter64
	MAX-ACCESS read-only
	STATUS current
	DESCRIPTION
		"The number of bytes passed. These are bytes processed by the policy."
	::= { ltmBwcPolicyStatEntry 5 }

ltmBwcPolicyStatBytesDropped OBJECT-TYPE
	SYNTAX Counter64
	MAX-ACCESS read-only
	STATUS current
	DESCRIPTION
		"The number of bytes dropped. These are bytes dropped by the policy."
	::= { ltmBwcPolicyStatEntry 6 }

ltmBwcPolicyStatPacketsIn OBJECT-TYPE
	SYNTAX Counter64
	MAX-ACCESS read-only
	STATUS current
	DESCRIPTION
		"The number of packets ingress. These are packets input to the policy
	        processing."
	::= { ltmBwcPolicyStatEntry 7 }

ltmBwcPolicyStatPacketsPassed OBJECT-TYPE
	SYNTAX Counter64
	MAX-ACCESS read-only
	STATUS current
	DESCRIPTION
		"The number of packets passed. These are packets passed by the policy."
	::= { ltmBwcPolicyStatEntry 8 }

ltmBwcPolicyStatActivePolicies OBJECT-TYPE
	SYNTAX Counter64
	MAX-ACCESS read-only
	STATUS current
	DESCRIPTION
		"The number of current policies. This is active number of current
	        policies in system."
	::= { ltmBwcPolicyStatEntry 9 }

ltmBwcPolicyStatInactivePolicies OBJECT-TYPE
	SYNTAX Counter64
	MAX-ACCESS read-only
	STATUS current
	DESCRIPTION
		"The number of inactive policies created. This is inactive number of
	        policies in the system."
	::= { ltmBwcPolicyStatEntry 10 }

ltmBwcPolicyStatTotalPolicies OBJECT-TYPE
	SYNTAX Counter64
	MAX-ACCESS read-only
	STATUS current
	DESCRIPTION
		"The number of total policies created. This is total number of
	        policies in system."
	::= { ltmBwcPolicyStatEntry 11 }

ltmBwcPolicyStatTimeDataCollected OBJECT-TYPE
	SYNTAX Counter64
	MAX-ACCESS read-only
	STATUS current
	DESCRIPTION
		"The time since start in seconds. This is the time since the stats
	        information has been collected."
	::= { ltmBwcPolicyStatEntry 12 }

ltmBwcPolicyStatPacketsPerSec OBJECT-TYPE
	SYNTAX Counter64
	MAX-ACCESS read-only
	STATUS current
	DESCRIPTION
		"The average input packets/sec over last 4 seconds. These are packets as
	        processed by this policy."
	::= { ltmBwcPolicyStatEntry 13 }

ltmBwcPolicyStatPacketsPerSecOut OBJECT-TYPE
	SYNTAX Counter64
	MAX-ACCESS read-only
	STATUS current
	DESCRIPTION
		"The average output packets/sec over last 4 seconds. These are packets
	        processed by this policy."
	::= { ltmBwcPolicyStatEntry 14 }

--==================================================================
-- Dns_security_query_type_filter
--==================================================================
ltmDnsQueryFilterNumber OBJECT-TYPE
	SYNTAX INTEGER
	MAX-ACCESS read-only
	STATUS current
	DESCRIPTION
		"The number of ltmDnsQueryFilter entries in the table."
	::= { ltmDnsQueryFilter 1 }

ltmDnsQueryFilterTable OBJECT-TYPE
	SYNTAX SEQUENCE OF LtmDnsQueryFilterEntry
	MAX-ACCESS not-accessible
	STATUS current
	DESCRIPTION
		"A table containing information of DNS query type filtering."
	::= { ltmDnsQueryFilter 2 }

ltmDnsQueryFilterEntry OBJECT-TYPE
	SYNTAX  LtmDnsQueryFilterEntry
	MAX-ACCESS not-accessible
	STATUS current
	DESCRIPTION
		"Columns in the ltmDnsQueryFilter Table"
	INDEX {
		ltmDnsQueryFilterName,
		ltmDnsQueryFilterIndex
	}
	::= { ltmDnsQueryFilterTable 1 }

LtmDnsQueryFilterEntry ::=
	SEQUENCE {
        	ltmDnsQueryFilterName                                     LongDisplayString,
        	ltmDnsQueryFilterIndex                                    INTEGER,
        	ltmDnsQueryFilterType                                     INTEGER
	}

ltmDnsQueryFilterName OBJECT-TYPE
	SYNTAX LongDisplayString
	MAX-ACCESS read-only
	STATUS current
	DESCRIPTION
		"The name of a DNS security profile."
	::= { ltmDnsQueryFilterEntry 1 }

ltmDnsQueryFilterIndex OBJECT-TYPE
	SYNTAX INTEGER(0..2147483647)
	MAX-ACCESS read-only
	STATUS current
	DESCRIPTION
		"The index of DNS query type filter for the specified DNS security profile."
	::= { ltmDnsQueryFilterEntry 2 }

ltmDnsQueryFilterType OBJECT-TYPE
	SYNTAX INTEGER {
		invalid(0),
		a(1),
		ns(2),
		md(3),
		mf(4),
		cname(5),
		soa(6),
		mb(7),
		mg(8),
		mr(9),
		null(10),
		wks(11),
		ptr(12),
		hinfo(13),
		minfo(14),
		mx(15),
		txt(16),
		rp(17),
		afsdb(18),
		x25(19),
		isdn(20),
		rt(21),
		nsap(22),
		nsapPtr(23),
		sg(24),
		key(25),
		px(26),
		gpos(27),
		aaaa(28),
		loc(29),
		nxt(30),
		eid(31),
		nimloc(32),
		srv(33),
		atma(34),
		naptr(35),
		kx(36),
		cert(37),
		a6(38),
		dname(39),
		sink(40),
		opt(41),
		tkey(249),
		tsig(250),
		ixfr(251),
		axfr(252),
		mailb(253),
		maila(254),
		any(255),
		zxfr(256),
		max(65536)
	}
	MAX-ACCESS read-only
	STATUS current
	DESCRIPTION
		"The DNS query type value that is either included or excluded
	         depending on the query_type_inclusion flag.  Value 0 (no)
	         implies disable (exclusion) and 1 (yes) is enable
	         (inclusion)."
	::= { ltmDnsQueryFilterEntry 3 }

--==================================================================
-- Dns_security_header_opcode_exclusion
--==================================================================
ltmDnsHeaderFilterNumber OBJECT-TYPE
	SYNTAX INTEGER
	MAX-ACCESS read-only
	STATUS current
	DESCRIPTION
		"The number of ltmDnsHeaderFilter entries in the table."
	::= { ltmDnsHeaderFilter 1 }

ltmDnsHeaderFilterTable OBJECT-TYPE
	SYNTAX SEQUENCE OF LtmDnsHeaderFilterEntry
	MAX-ACCESS not-accessible
	STATUS current
	DESCRIPTION
		"A table containing information of DNS header opcode filtering."
	::= { ltmDnsHeaderFilter 2 }

ltmDnsHeaderFilterEntry OBJECT-TYPE
	SYNTAX  LtmDnsHeaderFilterEntry
	MAX-ACCESS not-accessible
	STATUS current
	DESCRIPTION
		"Columns in the ltmDnsHeaderFilter Table"
	INDEX {
		ltmDnsHeaderFilterName,
		ltmDnsHeaderFilterIndex
	}
	::= { ltmDnsHeaderFilterTable 1 }

LtmDnsHeaderFilterEntry ::=
	SEQUENCE {
        	ltmDnsHeaderFilterName                                    LongDisplayString,
        	ltmDnsHeaderFilterIndex                                   INTEGER,
        	ltmDnsHeaderFilterOpcodeExclusion                         INTEGER
	}

ltmDnsHeaderFilterName OBJECT-TYPE
	SYNTAX LongDisplayString
	MAX-ACCESS read-only
	STATUS current
	DESCRIPTION
		"The name of a DNS security profile."
	::= { ltmDnsHeaderFilterEntry 1 }

ltmDnsHeaderFilterIndex OBJECT-TYPE
	SYNTAX INTEGER(0..2147483647)
	MAX-ACCESS read-only
	STATUS current
	DESCRIPTION
		"The index of DNS header opcode exclusion for the specified DNS security profile."
	::= { ltmDnsHeaderFilterEntry 2 }

ltmDnsHeaderFilterOpcodeExclusion OBJECT-TYPE
	SYNTAX INTEGER {
		query(0),
		iquery(1),
		status(2),
		notify(4),
		update(5)
	}
	MAX-ACCESS read-only
	STATUS current
	DESCRIPTION
		"The DNS header opcode values. Value of 3 is not used."
	::= { ltmDnsHeaderFilterEntry 3 }

--==================================================================
-- Lsn_prefix
--==================================================================
ltmLsnPrefixNumber OBJECT-TYPE
	SYNTAX INTEGER
	MAX-ACCESS read-only
	STATUS current
	DESCRIPTION
		"The number of ltmLsnPrefix entries in the table."
	::= { ltmLsnPrefix 1 }

ltmLsnPrefixTable OBJECT-TYPE
	SYNTAX SEQUENCE OF LtmLsnPrefixEntry
	MAX-ACCESS not-accessible
	STATUS current
	DESCRIPTION
		"A table containing information of LSN prefix."
	::= { ltmLsnPrefix 2 }

ltmLsnPrefixEntry OBJECT-TYPE
	SYNTAX  LtmLsnPrefixEntry
	MAX-ACCESS not-accessible
	STATUS current
	DESCRIPTION
		"Columns in the ltmLsnPrefix Table"
	INDEX {
		ltmLsnPrefixName
	}
	::= { ltmLsnPrefixTable 1 }

LtmLsnPrefixEntry ::=
	SEQUENCE {
        	ltmLsnPrefixName                                          LongDisplayString,
        	ltmLsnPrefixAddrType                                      InetAddressType,
        	ltmLsnPrefixAddr                                          InetAddress
	}

ltmLsnPrefixName OBJECT-TYPE
	SYNTAX LongDisplayString
	MAX-ACCESS read-only
	STATUS current
	DESCRIPTION
		"The name of a LSN prefix node."
	::= { ltmLsnPrefixEntry 1 }

ltmLsnPrefixAddrType OBJECT-TYPE
	SYNTAX InetAddressType
	MAX-ACCESS read-only
	STATUS current
	DESCRIPTION
		"The IP address type of ltmLsnPrefixAddr."
	::= { ltmLsnPrefixEntry 2 }

ltmLsnPrefixAddr OBJECT-TYPE
	SYNTAX InetAddress
	MAX-ACCESS read-only
	STATUS current
	DESCRIPTION
		"The IP address of a node. It is interpreted within
		 the context of a ltmLsnPrefixAddrType value."
	::= { ltmLsnPrefixEntry 3 }

--==================================================================
-- Lsn_pool
--==================================================================
ltmLsnPoolNumber OBJECT-TYPE
	SYNTAX INTEGER
	MAX-ACCESS read-only
	STATUS current
	DESCRIPTION
		"The number of ltmLsnPool entries in the table."
	::= { ltmLsnPool 1 }

ltmLsnPoolTable OBJECT-TYPE
	SYNTAX SEQUENCE OF LtmLsnPoolEntry
	MAX-ACCESS not-accessible
	STATUS current
	DESCRIPTION
		"A table containing information of LSN pool."
	::= { ltmLsnPool 2 }

ltmLsnPoolEntry OBJECT-TYPE
	SYNTAX  LtmLsnPoolEntry
	MAX-ACCESS not-accessible
	STATUS current
	DESCRIPTION
		"Columns in the ltmLsnPool Table"
	INDEX {
		ltmLsnPoolName
	}
	::= { ltmLsnPoolTable 1 }

LtmLsnPoolEntry ::=
	SEQUENCE {
        	ltmLsnPoolName                                            LongDisplayString,
        	ltmLsnPoolMemberCount                                     Gauge,
        	ltmLsnPoolRouteAdvertisement                              INTEGER,
        	ltmLsnPoolMode                                            INTEGER,
        	ltmLsnPoolPersistenceMode                                 INTEGER,
        	ltmLsnPoolPersistenceTimeout                              Gauge,
        	ltmLsnPoolPersistencePrefixLengthIpv4                     Gauge,
        	ltmLsnPoolPersistencePrefixLengthIpv6                     Gauge,
        	ltmLsnPoolInboundConnections                              INTEGER,
        	ltmLsnPoolIcmpEcho                                        INTEGER,
        	ltmLsnPoolTranslationPortRangeLow                         Gauge,
        	ltmLsnPoolTranslationPortRangeHigh                        Gauge,
        	ltmLsnPoolClientConnectionLimit                           Gauge,
        	ltmLsnPoolEgressInterfacesEnabled                         INTEGER,
        	ltmLsnPoolLogPublisher                                    LongDisplayString,
        	ltmLsnPoolHairpinMode                                     INTEGER,
        	ltmLsnPoolLogProfile                                      LongDisplayString
	}

ltmLsnPoolName OBJECT-TYPE
	SYNTAX LongDisplayString
	MAX-ACCESS read-only
	STATUS current
	DESCRIPTION
		"The name of a LSN Pool."
	::= { ltmLsnPoolEntry 1 }

ltmLsnPoolMemberCount OBJECT-TYPE
	SYNTAX Gauge
	MAX-ACCESS read-only
	STATUS current
	DESCRIPTION
		"The total number of members in the specified pool."
	::= { ltmLsnPoolEntry 2 }

ltmLsnPoolRouteAdvertisement OBJECT-TYPE
	SYNTAX INTEGER {
		false(0),
		true(1)
	}
	MAX-ACCESS read-only
	STATUS current
	DESCRIPTION
		"Specifies whether route advertisement is enabled or disabled for
	        translated IP addresses."
	::= { ltmLsnPoolEntry 3 }

ltmLsnPoolMode OBJECT-TYPE
	SYNTAX INTEGER {
		napt(0),
		pba(1),
		deterministic(2)
	}
	MAX-ACCESS read-only
	STATUS current
	DESCRIPTION
		"NAPT mode provides standard address and port translation
	        allowing multiple clients to share the same external address.
	    Deterministic mode provides address and port translations
	        that can be consistently reversed so that external address
	        and port combinations can identify specific clients."
	::= { ltmLsnPoolEntry 4 }

ltmLsnPoolPersistenceMode OBJECT-TYPE
	SYNTAX INTEGER {
		none(0),
		address(1),
		addressPort(2)
	}
	MAX-ACCESS read-only
	STATUS current
	DESCRIPTION
		"Persistence settings for LSN translation entries.
	        none: Specifies that there is no persistence for the translation.
	        address: Specifies that the translation reuses the port mapping for
	            subsequent packets sent from the same internal IP address and port
	            to the same external IP address while the mapping is still active,
	            regardless of the external port.
	        addressPort: Specifies that the translation reuses the port mapping
	            for subsequent packets sent from the same internal IP address
	            and port to the same external IP address and port while the
	            mapping is still active."
	::= { ltmLsnPoolEntry 5 }

ltmLsnPoolPersistenceTimeout OBJECT-TYPE
	SYNTAX Gauge
	MAX-ACCESS read-only
	STATUS current
	DESCRIPTION
		"Maximum time-to-live for inactive translation entries."
	::= { ltmLsnPoolEntry 6 }

ltmLsnPoolPersistencePrefixLengthIpv4 OBJECT-TYPE
	SYNTAX Gauge
	MAX-ACCESS read-only
	STATUS	 deprecated
	DESCRIPTION
		"Deprecated! This field is removed.
	    Number of significant bits in the client IPv4 address to be used as
	        the persistence key."
	::= { ltmLsnPoolEntry 7 }

ltmLsnPoolPersistencePrefixLengthIpv6 OBJECT-TYPE
	SYNTAX Gauge
	MAX-ACCESS read-only
	STATUS	 deprecated
	DESCRIPTION
		"Deprecated! This field is removed.
	    Number of significant bits in the client IPv6 address to be used as
	        the persistence key."
	::= { ltmLsnPoolEntry 8 }

ltmLsnPoolInboundConnections OBJECT-TYPE
	SYNTAX INTEGER {
		disabled(0),
		automatic(1),
		explicit(2)
	}
	MAX-ACCESS read-only
	STATUS current
	DESCRIPTION
		"If true, will enable inbound connections to translation addresses and ports."
	::= { ltmLsnPoolEntry 9 }

ltmLsnPoolIcmpEcho OBJECT-TYPE
	SYNTAX INTEGER {
		false(0),
		true(1)
	}
	MAX-ACCESS read-only
	STATUS current
	DESCRIPTION
		"If true, will enable icmp-echo requests for translation addresses."
	::= { ltmLsnPoolEntry 10 }

ltmLsnPoolTranslationPortRangeLow OBJECT-TYPE
	SYNTAX Gauge
	MAX-ACCESS read-only
	STATUS current
	DESCRIPTION
		"Specifies the low end of the range of port numbers available for use with
	        translation IP addresses."
	::= { ltmLsnPoolEntry 11 }

ltmLsnPoolTranslationPortRangeHigh OBJECT-TYPE
	SYNTAX Gauge
	MAX-ACCESS read-only
	STATUS current
	DESCRIPTION
		"Specifies the high end of the range of port numbers available for use with
	        translation IP addresses."
	::= { ltmLsnPoolEntry 12 }

ltmLsnPoolClientConnectionLimit OBJECT-TYPE
	SYNTAX Gauge
	MAX-ACCESS read-only
	STATUS current
	DESCRIPTION
		"Specifies the maximum number of simultaneous translated connections a client or
	        subscriber is allowed to have.  A value of zero signifies no limit."
	::= { ltmLsnPoolEntry 13 }

ltmLsnPoolEgressInterfacesEnabled OBJECT-TYPE
	SYNTAX INTEGER {
		false(0),
		true(1)
	}
	MAX-ACCESS read-only
	STATUS current
	DESCRIPTION
		"If true, source address translation is allowed on the interfaces specified in
	        the egress-interfaces list."
	::= { ltmLsnPoolEntry 14 }

ltmLsnPoolLogPublisher OBJECT-TYPE
	SYNTAX LongDisplayString
	MAX-ACCESS read-only
	STATUS current
	DESCRIPTION
		"Specifies the name of the log publisher that logs translation events, if any."
	::= { ltmLsnPoolEntry 15 }

ltmLsnPoolHairpinMode OBJECT-TYPE
	SYNTAX INTEGER {
		disabled(0),
		enabled(1)
	}
	MAX-ACCESS read-only
	STATUS current
	DESCRIPTION
		"If enabled, will enable hairpinning for inbound connections.  A hairpin connection between
	        two subscribers goes through the NAT device and uses translation addresses so that it
	        appears to each subscriber that the other is an external host."
	::= { ltmLsnPoolEntry 16 }

ltmLsnPoolLogProfile OBJECT-TYPE
	SYNTAX LongDisplayString
	MAX-ACCESS read-only
	STATUS current
	DESCRIPTION
		"Specifies the name of the log profile that control the logging of translation events, if any."
	::= { ltmLsnPoolEntry 17 }

--==================================================================
-- Lsn_prefix_lsn_pool
--==================================================================
ltmLsnPrefixLsnPoolNumber OBJECT-TYPE
	SYNTAX INTEGER
	MAX-ACCESS read-only
	STATUS current
	DESCRIPTION
		"The number of ltmLsnPrefixLsnPool entries in the table."
	::= { ltmLsnPrefixLsnPool 1 }

ltmLsnPrefixLsnPoolTable OBJECT-TYPE
	SYNTAX SEQUENCE OF LtmLsnPrefixLsnPoolEntry
	MAX-ACCESS not-accessible
	STATUS current
	DESCRIPTION
		"A table containing information of LSN pool prefix."
	::= { ltmLsnPrefixLsnPool 2 }

ltmLsnPrefixLsnPoolEntry OBJECT-TYPE
	SYNTAX  LtmLsnPrefixLsnPoolEntry
	MAX-ACCESS not-accessible
	STATUS current
	DESCRIPTION
		"Columns in the ltmLsnPrefixLsnPool Table"
	INDEX {
		ltmLsnPrefixLsnPoolLsnPoolName,
		ltmLsnPrefixLsnPoolLsnPrefixName
	}
	::= { ltmLsnPrefixLsnPoolTable 1 }

LtmLsnPrefixLsnPoolEntry ::=
	SEQUENCE {
        	ltmLsnPrefixLsnPoolLsnPrefixName                          LongDisplayString,
        	ltmLsnPrefixLsnPoolLsnPoolName                            LongDisplayString,
        	ltmLsnPrefixLsnPoolPrefixAddressType                      InetAddressType,
        	ltmLsnPrefixLsnPoolPrefixAddress                          InetAddress
	}

ltmLsnPrefixLsnPoolLsnPrefixName OBJECT-TYPE
	SYNTAX LongDisplayString
	MAX-ACCESS read-only
	STATUS current
	DESCRIPTION
		"The name of a LSN prefix node."
	::= { ltmLsnPrefixLsnPoolEntry 1 }

ltmLsnPrefixLsnPoolLsnPoolName OBJECT-TYPE
	SYNTAX LongDisplayString
	MAX-ACCESS read-only
	STATUS current
	DESCRIPTION
		"The name of a LSN pool."
	::= { ltmLsnPrefixLsnPoolEntry 2 }

ltmLsnPrefixLsnPoolPrefixAddressType OBJECT-TYPE
	SYNTAX InetAddressType
	MAX-ACCESS read-only
	STATUS current
	DESCRIPTION
		"The IP address type of ltmLsnPrefixLsnPoolPrefixAddress."
	::= { ltmLsnPrefixLsnPoolEntry 3 }

ltmLsnPrefixLsnPoolPrefixAddress OBJECT-TYPE
	SYNTAX InetAddress
	MAX-ACCESS read-only
	STATUS current
	DESCRIPTION
		"The IP address of a node. It is interpreted within
	        the context of a ltmLsnPrefixLsnPoolPrefixAddressType value."
	::= { ltmLsnPrefixLsnPoolEntry 4 }

--==================================================================
-- Lsn_prefix_lsn_pool_backup
--==================================================================
ltmLsnPrefixLsnPoolBackupNumber OBJECT-TYPE
	SYNTAX INTEGER
	MAX-ACCESS read-only
	STATUS current
	DESCRIPTION
		"The number of ltmLsnPrefixLsnPoolBackup entries in the table."
	::= { ltmLsnPrefixLsnPoolBackup 1 }

ltmLsnPrefixLsnPoolBackupTable OBJECT-TYPE
	SYNTAX SEQUENCE OF LtmLsnPrefixLsnPoolBackupEntry
	MAX-ACCESS not-accessible
	STATUS current
	DESCRIPTION
		"A table containing information of LSN pool backup prefix."
	::= { ltmLsnPrefixLsnPoolBackup 2 }

ltmLsnPrefixLsnPoolBackupEntry OBJECT-TYPE
	SYNTAX  LtmLsnPrefixLsnPoolBackupEntry
	MAX-ACCESS not-accessible
	STATUS current
	DESCRIPTION
		"Columns in the ltmLsnPrefixLsnPoolBackup Table"
	INDEX {
		ltmLsnPrefixLsnPoolBackupLsnPoolName,
		ltmLsnPrefixLsnPoolBackupLsnPrefixName
	}
	::= { ltmLsnPrefixLsnPoolBackupTable 1 }

LtmLsnPrefixLsnPoolBackupEntry ::=
	SEQUENCE {
        	ltmLsnPrefixLsnPoolBackupLsnPrefixName                    LongDisplayString,
        	ltmLsnPrefixLsnPoolBackupLsnPoolName                      LongDisplayString,
        	ltmLsnPrefixLsnPoolBackupPrefixAddressType                InetAddressType,
        	ltmLsnPrefixLsnPoolBackupPrefixAddress                    InetAddress
	}

ltmLsnPrefixLsnPoolBackupLsnPrefixName OBJECT-TYPE
	SYNTAX LongDisplayString
	MAX-ACCESS read-only
	STATUS current
	DESCRIPTION
		"The name of a LSN prefix node."
	::= { ltmLsnPrefixLsnPoolBackupEntry 1 }

ltmLsnPrefixLsnPoolBackupLsnPoolName OBJECT-TYPE
	SYNTAX LongDisplayString
	MAX-ACCESS read-only
	STATUS current
	DESCRIPTION
		"The name of a LSN pool."
	::= { ltmLsnPrefixLsnPoolBackupEntry 2 }

ltmLsnPrefixLsnPoolBackupPrefixAddressType OBJECT-TYPE
	SYNTAX InetAddressType
	MAX-ACCESS read-only
	STATUS current
	DESCRIPTION
		"The IP address type of ltmLsnPrefixLsnPoolBackupPrefixAddress."
	::= { ltmLsnPrefixLsnPoolBackupEntry 3 }

ltmLsnPrefixLsnPoolBackupPrefixAddress OBJECT-TYPE
	SYNTAX InetAddress
	MAX-ACCESS read-only
	STATUS current
	DESCRIPTION
		"The IP address of a node. It is interpreted within
	        the context of a ltmLsnPrefixLsnPoolBackupPrefixAddressType value."
	::= { ltmLsnPrefixLsnPoolBackupEntry 4 }

--==================================================================
-- Lsn_pool_vlan
--==================================================================
ltmLsnPoolVlanNumber OBJECT-TYPE
	SYNTAX INTEGER
	MAX-ACCESS read-only
	STATUS current
	DESCRIPTION
		"The number of ltmLsnPoolVlan entries in the table."
	::= { ltmLsnPoolVlan 1 }

ltmLsnPoolVlanTable OBJECT-TYPE
	SYNTAX SEQUENCE OF LtmLsnPoolVlanEntry
	MAX-ACCESS not-accessible
	STATUS current
	DESCRIPTION
		"A table containing VLAN information of LSN pool."
	::= { ltmLsnPoolVlan 2 }

ltmLsnPoolVlanEntry OBJECT-TYPE
	SYNTAX  LtmLsnPoolVlanEntry
	MAX-ACCESS not-accessible
	STATUS current
	DESCRIPTION
		"Columns in the ltmLsnPoolVlan Table"
	INDEX {
		ltmLsnPoolVlanLsnPoolName,
		ltmLsnPoolVlanVlanName
	}
	::= { ltmLsnPoolVlanTable 1 }

LtmLsnPoolVlanEntry ::=
	SEQUENCE {
        	ltmLsnPoolVlanLsnPoolName                                 LongDisplayString,
        	ltmLsnPoolVlanVlanName                                    LongDisplayString
	}

ltmLsnPoolVlanLsnPoolName OBJECT-TYPE
	SYNTAX LongDisplayString
	MAX-ACCESS read-only
	STATUS current
	DESCRIPTION
		"The name of a LSN pool."
	::= { ltmLsnPoolVlanEntry 1 }

ltmLsnPoolVlanVlanName OBJECT-TYPE
	SYNTAX LongDisplayString
	MAX-ACCESS read-only
	STATUS current
	DESCRIPTION
		"The name of VLAN for LSN pool."
	::= { ltmLsnPoolVlanEntry 2 }

--==================================================================
-- Lsn_pool_stat
--==================================================================
ltmLsnPoolStatResetStats OBJECT-TYPE
	SYNTAX INTEGER
	MAX-ACCESS read-write
	STATUS current
	DESCRIPTION
		"The action to reset resettable statistics data in ltmLsnPoolStat.
		 Setting this value to 1 will reset statistics data.
		 Note, some statistics data may not be reset including data that are incremental counters."
	::= { ltmLsnPoolStat 1 }

ltmLsnPoolStatNumber OBJECT-TYPE
	SYNTAX INTEGER
	MAX-ACCESS read-only
	STATUS current
	DESCRIPTION
		"The number of ltmLsnPoolStat entries in the table."
	::= { ltmLsnPoolStat 2 }

ltmLsnPoolStatTable OBJECT-TYPE
	SYNTAX SEQUENCE OF LtmLsnPoolStatEntry
	MAX-ACCESS not-accessible
	STATUS current
	DESCRIPTION
		"A table containing statistic information of LSN pool."
	::= { ltmLsnPoolStat 3 }

ltmLsnPoolStatEntry OBJECT-TYPE
	SYNTAX  LtmLsnPoolStatEntry
	MAX-ACCESS not-accessible
	STATUS current
	DESCRIPTION
		"Columns in the ltmLsnPoolStat Table"
	INDEX {
		ltmLsnPoolStatName
	}
	::= { ltmLsnPoolStatTable 1 }

LtmLsnPoolStatEntry ::=
	SEQUENCE {
        	ltmLsnPoolStatName                                        LongDisplayString,
        	ltmLsnPoolStatTranslationRequests                         Counter64,
        	ltmLsnPoolStatHairpinConnectionRequests                   Counter64,
        	ltmLsnPoolStatActiveTranslations                          Counter64,
        	ltmLsnPoolStatActiveHairpinConnections                    Counter64,
        	ltmLsnPoolStatTranslationRequestFailures                  Counter64,
        	ltmLsnPoolStatPersistenceMappingFailures                  Counter64,
        	ltmLsnPoolStatHairpinConnectionFailures                   Counter64,
        	ltmLsnPoolStatBackupPoolTranslations                      Counter64,
        	ltmLsnPoolStatLogAttempts                                 Counter64,
        	ltmLsnPoolStatLogFailures                                 Counter64,
        	ltmLsnPoolStatTotalEndPoints                              Counter64,
        	ltmLsnPoolStatPcpAnnounceRequests                         Counter64,
        	ltmLsnPoolStatPcpAnnounceResponsesUcast                   Counter64,
        	ltmLsnPoolStatPcpAnnounceResponsesMulticast               Counter64,
        	ltmLsnPoolStatPcpMapRequests                              Counter64,
        	ltmLsnPoolStatPcpMapResponses                             Counter64,
        	ltmLsnPoolStatPcpPeerRequests                             Counter64,
        	ltmLsnPoolStatPcpPeerResponses                            Counter64,
        	ltmLsnPoolStatPcpErrorsInvalidRequest                     Counter64,
        	ltmLsnPoolStatPcpErrorsUnavailableResource                Counter64,
        	ltmLsnPoolStatPcpErrorsNotAuthorized                      Counter64,
        	ltmLsnPoolStatPcpErrorsOther                              Counter64,
        	ltmLsnPoolStatActivePortBlocks                            Counter64,
        	ltmLsnPoolStatActiveClientsReachedLimit                   Counter64,
        	ltmLsnPoolStatActiveZombiePortBlocks                      Counter64,
        	ltmLsnPoolStatTotalClientsReachedLimit                    Counter64,
        	ltmLsnPoolStatTotalPortBlockAllocations                   Counter64,
        	ltmLsnPoolStatTotalPortBlockAllocationFailures            Counter64,
        	ltmLsnPoolStatTotalPortBlockDeallocations                 Counter64,
        	ltmLsnPoolStatTotalZombiePortBlocksCreated                Counter64,
        	ltmLsnPoolStatTotalZombiePortBlocksDeleted                Counter64,
        	ltmLsnPoolStatTotalZombiePortBlockConnsKilled             Counter64,
        	ltmLsnPoolStatEndPointsString                             LongDisplayString,
        	ltmLsnPoolStatTotalPortBlocks                             Counter64,
        	ltmLsnPoolStatPercentFreePortBlocksSnmp                   Counter64
	}

ltmLsnPoolStatName OBJECT-TYPE
	SYNTAX LongDisplayString
	MAX-ACCESS read-only
	STATUS current
	DESCRIPTION
		"The name of a LSN Pool."
	::= { ltmLsnPoolStatEntry 1 }

ltmLsnPoolStatTranslationRequests OBJECT-TYPE
	SYNTAX Counter64
	MAX-ACCESS read-only
	STATUS current
	DESCRIPTION
		"The number of translation requests."
	::= { ltmLsnPoolStatEntry 2 }

ltmLsnPoolStatHairpinConnectionRequests OBJECT-TYPE
	SYNTAX Counter64
	MAX-ACCESS read-only
	STATUS current
	DESCRIPTION
		"The number of hairpin connection requests.  A hairpin connection between
	        two subscribers goes through the NAT device and uses translation addresses so
	        that it appears to each subscriber that the other is an external host."
	::= { ltmLsnPoolStatEntry 3 }

ltmLsnPoolStatActiveTranslations OBJECT-TYPE
	SYNTAX Counter64
	MAX-ACCESS read-only
	STATUS current
	DESCRIPTION
		"The number of active translations."
	::= { ltmLsnPoolStatEntry 4 }

ltmLsnPoolStatActiveHairpinConnections OBJECT-TYPE
	SYNTAX Counter64
	MAX-ACCESS read-only
	STATUS current
	DESCRIPTION
		"The number of active hairpin connections.  A hairpin connection between
	        two subscribers goes through the NAT device and uses translation addresses so
	        that it appears to each subscriber that the other is an external host."
	::= { ltmLsnPoolStatEntry 5 }

ltmLsnPoolStatTranslationRequestFailures OBJECT-TYPE
	SYNTAX Counter64
	MAX-ACCESS read-only
	STATUS current
	DESCRIPTION
		"The number of translation request failures."
	::= { ltmLsnPoolStatEntry 6 }

ltmLsnPoolStatPersistenceMappingFailures OBJECT-TYPE
	SYNTAX Counter64
	MAX-ACCESS read-only
	STATUS current
	DESCRIPTION
		"The number of persistence mapping translation request failures."
	::= { ltmLsnPoolStatEntry 7 }

ltmLsnPoolStatHairpinConnectionFailures OBJECT-TYPE
	SYNTAX Counter64
	MAX-ACCESS read-only
	STATUS current
	DESCRIPTION
		"The number of failed hairpin connections.  A hairpin connection failure
	        occurs when a subscriber connects to an inbound reservation but a connection
	        could not be created."
	::= { ltmLsnPoolStatEntry 8 }

ltmLsnPoolStatBackupPoolTranslations OBJECT-TYPE
	SYNTAX Counter64
	MAX-ACCESS read-only
	STATUS current
	DESCRIPTION
		"The number of translation requests that were served using the backup pool."
	::= { ltmLsnPoolStatEntry 9 }

ltmLsnPoolStatLogAttempts OBJECT-TYPE
	SYNTAX Counter64
	MAX-ACCESS read-only
	STATUS current
	DESCRIPTION
		"The number of logging attempts."
	::= { ltmLsnPoolStatEntry 10 }

ltmLsnPoolStatLogFailures OBJECT-TYPE
	SYNTAX Counter64
	MAX-ACCESS read-only
	STATUS current
	DESCRIPTION
		"The number of logging attempts that resulted in failure."
	::= { ltmLsnPoolStatEntry 11 }

ltmLsnPoolStatTotalEndPoints OBJECT-TYPE
	SYNTAX Counter64
	MAX-ACCESS read-only
	STATUS current
	DESCRIPTION
		"The product of the number of IP addresses and the translation port
	        range. This is computed when the pool membership or translation
	        port range changes."
	::= { ltmLsnPoolStatEntry 12 }

ltmLsnPoolStatPcpAnnounceRequests OBJECT-TYPE
	SYNTAX Counter64
	MAX-ACCESS read-only
	STATUS current
	DESCRIPTION
		"The total number of PCP Announce requests received."
	::= { ltmLsnPoolStatEntry 13 }

ltmLsnPoolStatPcpAnnounceResponsesUcast OBJECT-TYPE
	SYNTAX Counter64
	MAX-ACCESS read-only
	STATUS current
	DESCRIPTION
		"The total number of unicast PCP Announce responses transmitted."
	::= { ltmLsnPoolStatEntry 14 }

ltmLsnPoolStatPcpAnnounceResponsesMulticast OBJECT-TYPE
	SYNTAX Counter64
	MAX-ACCESS read-only
	STATUS current
	DESCRIPTION
		"The total number of multicast PCP Announce responses transmitted."
	::= { ltmLsnPoolStatEntry 15 }

ltmLsnPoolStatPcpMapRequests OBJECT-TYPE
	SYNTAX Counter64
	MAX-ACCESS read-only
	STATUS current
	DESCRIPTION
		"The total number of PCP Map requests received."
	::= { ltmLsnPoolStatEntry 16 }

ltmLsnPoolStatPcpMapResponses OBJECT-TYPE
	SYNTAX Counter64
	MAX-ACCESS read-only
	STATUS current
	DESCRIPTION
		"The total number of PCP Map responses transmitted."
	::= { ltmLsnPoolStatEntry 17 }

ltmLsnPoolStatPcpPeerRequests OBJECT-TYPE
	SYNTAX Counter64
	MAX-ACCESS read-only
	STATUS current
	DESCRIPTION
		"The total number of PCP Peer requests received."
	::= { ltmLsnPoolStatEntry 18 }

ltmLsnPoolStatPcpPeerResponses OBJECT-TYPE
	SYNTAX Counter64
	MAX-ACCESS read-only
	STATUS current
	DESCRIPTION
		"The total number of PCP Peer responses transmitted."
	::= { ltmLsnPoolStatEntry 19 }

ltmLsnPoolStatPcpErrorsInvalidRequest OBJECT-TYPE
	SYNTAX Counter64
	MAX-ACCESS read-only
	STATUS current
	DESCRIPTION
		"The total number of invalid or malformed PCP requests received."
	::= { ltmLsnPoolStatEntry 20 }

ltmLsnPoolStatPcpErrorsUnavailableResource OBJECT-TYPE
	SYNTAX Counter64
	MAX-ACCESS read-only
	STATUS current
	DESCRIPTION
		"The total number of PCP requests received where the server has insufficient
	     resources to complete the requested operation."
	::= { ltmLsnPoolStatEntry 21 }

ltmLsnPoolStatPcpErrorsNotAuthorized OBJECT-TYPE
	SYNTAX Counter64
	MAX-ACCESS read-only
	STATUS current
	DESCRIPTION
		"The total number of PCP requests that generated (or caused) an
	    unauthorized error when attempting to create a mapping."
	::= { ltmLsnPoolStatEntry 22 }

ltmLsnPoolStatPcpErrorsOther OBJECT-TYPE
	SYNTAX Counter64
	MAX-ACCESS read-only
	STATUS current
	DESCRIPTION
		"The total number of PCP requests received that resulted in other errors."
	::= { ltmLsnPoolStatEntry 23 }

ltmLsnPoolStatActivePortBlocks OBJECT-TYPE
	SYNTAX Counter64
	MAX-ACCESS read-only
	STATUS current
	DESCRIPTION
		"The total number of port blocks actively in use."
	::= { ltmLsnPoolStatEntry 24 }

ltmLsnPoolStatActiveClientsReachedLimit OBJECT-TYPE
	SYNTAX Counter64
	MAX-ACCESS read-only
	STATUS current
	DESCRIPTION
		"Total clients who have reached the max port blocks allocated to them."
	::= { ltmLsnPoolStatEntry 25 }

ltmLsnPoolStatActiveZombiePortBlocks OBJECT-TYPE
	SYNTAX Counter64
	MAX-ACCESS read-only
	STATUS current
	DESCRIPTION
		"Total blocks which have reached their lifetime and cannot be used for
	     	new allocations. They are not yet deleted because there are
	     	connections using ports in that block."
	::= { ltmLsnPoolStatEntry 26 }

ltmLsnPoolStatTotalClientsReachedLimit OBJECT-TYPE
	SYNTAX Counter64
	MAX-ACCESS read-only
	STATUS current
	DESCRIPTION
		"Total client connections rejected because client hit
	        client-block-limit and could not find any free ports in the
	        existing blocks."
	::= { ltmLsnPoolStatEntry 27 }

ltmLsnPoolStatTotalPortBlockAllocations OBJECT-TYPE
	SYNTAX Counter64
	MAX-ACCESS read-only
	STATUS current
	DESCRIPTION
		"Total port block allocations."
	::= { ltmLsnPoolStatEntry 28 }

ltmLsnPoolStatTotalPortBlockAllocationFailures OBJECT-TYPE
	SYNTAX Counter64
	MAX-ACCESS read-only
	STATUS current
	DESCRIPTION
		"Total port block allocation failures."
	::= { ltmLsnPoolStatEntry 29 }

ltmLsnPoolStatTotalPortBlockDeallocations OBJECT-TYPE
	SYNTAX Counter64
	MAX-ACCESS read-only
	STATUS current
	DESCRIPTION
		"Total port blocks freed."
	::= { ltmLsnPoolStatEntry 30 }

ltmLsnPoolStatTotalZombiePortBlocksCreated OBJECT-TYPE
	SYNTAX Counter64
	MAX-ACCESS read-only
	STATUS current
	DESCRIPTION
		"Total blocks which have reached their lifetime and cannot be used for
	        new allocations. They are not yet deleted because there are
	        connections using ports in that block."
	::= { ltmLsnPoolStatEntry 31 }

ltmLsnPoolStatTotalZombiePortBlocksDeleted OBJECT-TYPE
	SYNTAX Counter64
	MAX-ACCESS read-only
	STATUS current
	DESCRIPTION
		"Total zombie blocks deleted after their zombie timeouts. When a zombie
	        block is deleted, the connections using them are killed."
	::= { ltmLsnPoolStatEntry 32 }

ltmLsnPoolStatTotalZombiePortBlockConnsKilled OBJECT-TYPE
	SYNTAX Counter64
	MAX-ACCESS read-only
	STATUS current
	DESCRIPTION
		"Total connections killed due to zombie block reaching zombie timeout."
	::= { ltmLsnPoolStatEntry 33 }

ltmLsnPoolStatEndPointsString OBJECT-TYPE
	SYNTAX LongDisplayString
	MAX-ACCESS read-only
	STATUS current
	DESCRIPTION
		"The product of the number of IP addresses and the translation port
	        range. This is computed when the pool membership or translation
	        port range changes."
	::= { ltmLsnPoolStatEntry 34 }

ltmLsnPoolStatTotalPortBlocks OBJECT-TYPE
	SYNTAX Counter64
	MAX-ACCESS read-only
	STATUS current
	DESCRIPTION
		"The total number of port blocks."
	::= { ltmLsnPoolStatEntry 35 }

ltmLsnPoolStatPercentFreePortBlocksSnmp OBJECT-TYPE
	SYNTAX Counter64
	MAX-ACCESS read-only
	STATUS current
	DESCRIPTION
		"The percentage of free port blocks."
	::= { ltmLsnPoolStatEntry 36 }

--==================================================================
-- Profile_spdy
--==================================================================
ltmSpdyProfileNumber OBJECT-TYPE
	SYNTAX INTEGER
	MAX-ACCESS read-only
	STATUS	 deprecated
	DESCRIPTION
		"Deprecated!.
		The number of ltmSpdyProfile entries in the table."
	::= { ltmSpdyProfile 1 }

ltmSpdyProfileTable OBJECT-TYPE
	SYNTAX SEQUENCE OF LtmSpdyProfileEntry
	MAX-ACCESS not-accessible
	STATUS deprecated
	DESCRIPTION
		"Deprecated! A table containing information about the SPDY profile."
	::= { ltmSpdyProfile 2 }

ltmSpdyProfileEntry OBJECT-TYPE
	SYNTAX  LtmSpdyProfileEntry
	MAX-ACCESS not-accessible
	STATUS deprecated
	DESCRIPTION
		"Columns in the ltmSpdyProfile Table"
	INDEX {
		ltmSpdyProfileName
	}
	::= { ltmSpdyProfileTable 1 }

LtmSpdyProfileEntry ::=
	SEQUENCE {
        	ltmSpdyProfileName                                        LongDisplayString,
        	ltmSpdyProfileConfigSource                                INTEGER,
        	ltmSpdyProfileDefaultName                                 LongDisplayString,
        	ltmSpdyProfileActivationMode                              INTEGER,
        	ltmSpdyProfilePriorityHandling                            INTEGER,
        	ltmSpdyProfileInsertHeader                                INTEGER,
        	ltmSpdyProfileInsertHeaderName                            LongDisplayString,
        	ltmSpdyProfileConcurrentStreamsPerConnection              Gauge,
        	ltmSpdyProfileConnectionIdleTimeout                       Gauge,
        	ltmSpdyProfileReceiveWindow                               Gauge,
        	ltmSpdyProfileFrameSize                                   Gauge,
        	ltmSpdyProfileWriteSize                                   Gauge,
        	ltmSpdyProfileCompressionLevel                            Gauge,
        	ltmSpdyProfileCompressionWindowSize                       Gauge
	}

ltmSpdyProfileName OBJECT-TYPE
	SYNTAX LongDisplayString
	MAX-ACCESS read-only
	STATUS	 deprecated
	DESCRIPTION
		"Deprecated! The name of a SPDY profile."
	::= { ltmSpdyProfileEntry 1 }

ltmSpdyProfileConfigSource OBJECT-TYPE
	SYNTAX INTEGER {
		usercfg(0),
		basecfg(1)
	}
	MAX-ACCESS read-only
	STATUS	 deprecated
	DESCRIPTION
		"Deprecated! The state that specifies whether this is a base/pre-configured profile
		or user defined profile."
	::= { ltmSpdyProfileEntry 2 }

ltmSpdyProfileDefaultName OBJECT-TYPE
	SYNTAX LongDisplayString
	MAX-ACCESS read-only
	STATUS	 deprecated
	DESCRIPTION
		"Deprecated! The name of the profile from which the specified profile derives
		its attribute default values."
	::= { ltmSpdyProfileEntry 3 }

ltmSpdyProfileActivationMode OBJECT-TYPE
	SYNTAX INTEGER {
		npn(0),
		always(1)
	}
	MAX-ACCESS read-only
	STATUS	 deprecated
	DESCRIPTION
		"Deprecated! The manner in which SPDY connections are made.
	         npn - TLS Extension, Next Protocol Negotiation is used to decide which
	               SPDY protocol is used.
	         always - All connections will be assumed to be SPDY connections.
	                  Clients that only support HTTP will not be supported."
	::= { ltmSpdyProfileEntry 4 }

ltmSpdyProfilePriorityHandling OBJECT-TYPE
	SYNTAX INTEGER {
		strict(0),
		fair(1)
	}
	MAX-ACCESS read-only
	STATUS	 deprecated
	DESCRIPTION
		"Deprecated! The manner in which streams of different priorities are handled.
	         strict - Higher priority streams will be processed to completion
	                  before lower priority streams are processed.
	         fair - Higher priority streams will use more bandwidth than lower
	                priority streams without completely blocking the lower priority
	                streams."
	::= { ltmSpdyProfileEntry 5 }

ltmSpdyProfileInsertHeader OBJECT-TYPE
	SYNTAX INTEGER {
		false(0),
		true(1)
	}
	MAX-ACCESS read-only
	STATUS	 deprecated
	DESCRIPTION
		"Deprecated! The state indicating whether or not an HTTP header that indicates the
	         use of SPDY should be inserted into the request going to the back-end
	         server."
	::= { ltmSpdyProfileEntry 6 }

ltmSpdyProfileInsertHeaderName OBJECT-TYPE
	SYNTAX LongDisplayString
	MAX-ACCESS read-only
	STATUS	 deprecated
	DESCRIPTION
		"Deprecated! The HTTP header inserted into the request going to the back-end server,
	         if that functionality is enabled."
	::= { ltmSpdyProfileEntry 7 }

ltmSpdyProfileConcurrentStreamsPerConnection OBJECT-TYPE
	SYNTAX Gauge
	MAX-ACCESS read-only
	STATUS	 deprecated
	DESCRIPTION
		"Deprecated! The maximum amount of concurrent streams allowed per connection."
	::= { ltmSpdyProfileEntry 8 }

ltmSpdyProfileConnectionIdleTimeout OBJECT-TYPE
	SYNTAX Gauge
	MAX-ACCESS read-only
	STATUS	 deprecated
	DESCRIPTION
		"Deprecated! The amount of time, in seconds, a connection is open idly before it is
	         shutdown."
	::= { ltmSpdyProfileEntry 9 }

ltmSpdyProfileReceiveWindow OBJECT-TYPE
	SYNTAX Gauge
	MAX-ACCESS read-only
	STATUS	 deprecated
	DESCRIPTION
		"Deprecated! Specifies the size of the receive window in kilobytes. The receive
	         window is a mechanism to stall individual upload streams when needed.
	         This mechanism is only available for SPDY version 3 connections."
	::= { ltmSpdyProfileEntry 10 }

ltmSpdyProfileFrameSize OBJECT-TYPE
	SYNTAX Gauge
	MAX-ACCESS read-only
	STATUS	 deprecated
	DESCRIPTION
		"Deprecated! Specifies the size of the data frames, in bytes, that SPDY will send to
	         the client. Larger frame sizes will improve network utilization, but
	         may affect concurrency."
	::= { ltmSpdyProfileEntry 11 }

ltmSpdyProfileWriteSize OBJECT-TYPE
	SYNTAX Gauge
	MAX-ACCESS read-only
	STATUS	 deprecated
	DESCRIPTION
		"Deprecated! Specifies the total size of combined data frames, in bytes, SPDY will
	         send in a single write. This controls the size of the TLS records when
	         SPDY is used over SSL. A large write size will cause SPDY to buffer
	         more data, but will improve network utilization."
	::= { ltmSpdyProfileEntry 12 }

ltmSpdyProfileCompressionLevel OBJECT-TYPE
	SYNTAX Gauge
	MAX-ACCESS read-only
	STATUS	 deprecated
	DESCRIPTION
		"Deprecated! Specifies the amount of compression to do by default for the headers of
	         the specified profiles. The compression level must be between 0 and
	         10. Higher numbers correspond to more compression."
	::= { ltmSpdyProfileEntry 13 }

ltmSpdyProfileCompressionWindowSize OBJECT-TYPE
	SYNTAX Gauge
	MAX-ACCESS read-only
	STATUS	 deprecated
	DESCRIPTION
		"Deprecated! Specifies the size of the compression window for the specified profiles in
	         kilobytes. The compression window size must be between 1 and 128
	         kilobytes."
	::= { ltmSpdyProfileEntry 14 }

--==================================================================
-- Profile_spdy_protocol_versions
--==================================================================
ltmSpdyProfileProtocolVersionsNumber OBJECT-TYPE
	SYNTAX INTEGER
	MAX-ACCESS read-only
	STATUS	 deprecated
	DESCRIPTION
		"Deprecated!.
		The number of ltmSpdyProfileProtocolVersions entries in the table."
	::= { ltmSpdyProfileProtocolVersions 1 }

ltmSpdyProfileProtocolVersionsTable OBJECT-TYPE
	SYNTAX SEQUENCE OF LtmSpdyProfileProtocolVersionsEntry
	MAX-ACCESS not-accessible
	STATUS deprecated
	DESCRIPTION
		"Deprecated! A table containing information on the supported SPDY protocol
	        versions."
	::= { ltmSpdyProfileProtocolVersions 2 }

ltmSpdyProfileProtocolVersionsEntry OBJECT-TYPE
	SYNTAX  LtmSpdyProfileProtocolVersionsEntry
	MAX-ACCESS not-accessible
	STATUS deprecated
	DESCRIPTION
		"Columns in the ltmSpdyProfileProtocolVersions Table"
	INDEX {
		ltmSpdyProfileProtocolVersionsName,
		ltmSpdyProfileProtocolVersionsIndex
	}
	::= { ltmSpdyProfileProtocolVersionsTable 1 }

LtmSpdyProfileProtocolVersionsEntry ::=
	SEQUENCE {
        	ltmSpdyProfileProtocolVersionsName                        LongDisplayString,
        	ltmSpdyProfileProtocolVersionsIndex                       INTEGER,
        	ltmSpdyProfileProtocolVersionsProtocolVersions            INTEGER
	}

ltmSpdyProfileProtocolVersionsName OBJECT-TYPE
	SYNTAX LongDisplayString
	MAX-ACCESS read-only
	STATUS	 deprecated
	DESCRIPTION
		"Deprecated! The name of a SPDY profile."
	::= { ltmSpdyProfileProtocolVersionsEntry 1 }

ltmSpdyProfileProtocolVersionsIndex OBJECT-TYPE
	SYNTAX INTEGER(0..2147483647)
	MAX-ACCESS read-only
	STATUS	 deprecated
	DESCRIPTION
		"Deprecated! The index of the protocol versions used to determine which SPDY
	         versions are supported and in what order those versions should be
	         prioritized when deciding which version to use. This prioritization is
	         only used when the activation mode is set to npn."
	::= { ltmSpdyProfileProtocolVersionsEntry 2 }

ltmSpdyProfileProtocolVersionsProtocolVersions OBJECT-TYPE
	SYNTAX INTEGER {
		spdy2(1),
		spdy3(2),
		http11(3)
	}
	MAX-ACCESS read-only
	STATUS	 deprecated
	DESCRIPTION
		"Deprecated! The SPDY version supported.
	         spdy2 - indicates that SPDY version 2 is supported.
	         spdy3 - indicates that SPDY version 3 is supported.
	         http11 - indicates that HTTP1.1 is supported when SPDY is not
	                  supported/requested by a client."
	::= { ltmSpdyProfileProtocolVersionsEntry 3 }

--==================================================================
-- Profile_spdy_stat
--==================================================================
ltmSpdyProfileStatResetStats OBJECT-TYPE
	SYNTAX INTEGER
	MAX-ACCESS read-write
	STATUS	 deprecated
	DESCRIPTION
		"Deprecated!.
		The action to reset resettable statistics data in ltmSpdyProfileStat.
		 Setting this value to 1 will reset statistics data.
		 Note, some statistics data may not be reset including data that are incremental counters."
	::= { ltmSpdyProfileStat 1 }

ltmSpdyProfileStatNumber OBJECT-TYPE
	SYNTAX INTEGER
	MAX-ACCESS read-only
	STATUS	 deprecated
	DESCRIPTION
		"Deprecated!.
		The number of ltmSpdyProfileStat entries in the table."
	::= { ltmSpdyProfileStat 2 }

ltmSpdyProfileStatTable OBJECT-TYPE
	SYNTAX SEQUENCE OF LtmSpdyProfileStatEntry
	MAX-ACCESS not-accessible
	STATUS deprecated
	DESCRIPTION
		"Deprecated! A table containing statistics information about the SPDY profile."
	::= { ltmSpdyProfileStat 3 }

ltmSpdyProfileStatEntry OBJECT-TYPE
	SYNTAX  LtmSpdyProfileStatEntry
	MAX-ACCESS not-accessible
	STATUS deprecated
	DESCRIPTION
		"Columns in the ltmSpdyProfileStat Table"
	INDEX {
		ltmSpdyProfileStatName
	}
	::= { ltmSpdyProfileStatTable 1 }

LtmSpdyProfileStatEntry ::=
	SEQUENCE {
        	ltmSpdyProfileStatName                                    LongDisplayString,
        	ltmSpdyProfileStatConnectionsAccepted                     Counter64,
        	ltmSpdyProfileStatConnectionsCurrent                      Counter64,
        	ltmSpdyProfileStatConnectionsMax                          Counter64,
        	ltmSpdyProfileStatDataFramesReceived                      Counter64,
        	ltmSpdyProfileStatDataFramesSent                          Counter64,
        	ltmSpdyProfileStatFlowsCreated                            Counter64,
        	ltmSpdyProfileStatFlowsCurrent                            Counter64,
        	ltmSpdyProfileStatFlowsMax                                Counter64,
        	ltmSpdyProfileStatGoawayFramesReceived                    Counter64,
        	ltmSpdyProfileStatGoawayFramesSent                        Counter64,
        	ltmSpdyProfileStatHeadersFramesReceived                   Counter64,
        	ltmSpdyProfileStatHeadersFramesSent                       Counter64,
        	ltmSpdyProfileStatHttpRequestBytes                        Counter64,
        	ltmSpdyProfileStatHttpResponseBytes                       Counter64,
        	ltmSpdyProfileStatNoopFramesReceived                      Counter64,
        	ltmSpdyProfileStatNoopFramesSent                          Counter64,
        	ltmSpdyProfileStatPingFramesReceived                      Counter64,
        	ltmSpdyProfileStatPingFramesSent                          Counter64,
        	ltmSpdyProfileStatRstStreamFramesReceived                 Counter64,
        	ltmSpdyProfileStatRstStreamFramesSent                     Counter64,
        	ltmSpdyProfileStatSettingsFramesReceived                  Counter64,
        	ltmSpdyProfileStatSettingsFramesSent                      Counter64,
        	ltmSpdyProfileStatSpdyRequestBytes                        Counter64,
        	ltmSpdyProfileStatSpdyRequestFrames                       Counter64,
        	ltmSpdyProfileStatSpdyResponseBytes                       Counter64,
        	ltmSpdyProfileStatSpdyResponseFrames                      Counter64,
        	ltmSpdyProfileStatSynReplyFramesReceived                  Counter64,
        	ltmSpdyProfileStatSynReplyFramesSent                      Counter64,
        	ltmSpdyProfileStatSynStreamFramesReceived                 Counter64,
        	ltmSpdyProfileStatSynStreamFramesSent                     Counter64,
        	ltmSpdyProfileStatV2StreamsCreated                        Counter64,
        	ltmSpdyProfileStatV2StreamsCurrent                        Counter64,
        	ltmSpdyProfileStatV2StreamsMax                            Counter64,
        	ltmSpdyProfileStatV3StreamsCreated                        Counter64,
        	ltmSpdyProfileStatV3StreamsCurrent                        Counter64,
        	ltmSpdyProfileStatV3StreamsMax                            Counter64,
        	ltmSpdyProfileStatWindowUpdateFramesReceived              Counter64,
        	ltmSpdyProfileStatWindowUpdateFramesSent                  Counter64
	}

ltmSpdyProfileStatName OBJECT-TYPE
	SYNTAX LongDisplayString
	MAX-ACCESS read-only
	STATUS	 deprecated
	DESCRIPTION
		"Deprecated! The name of the SPDY profile."
	::= { ltmSpdyProfileStatEntry 1 }

ltmSpdyProfileStatConnectionsAccepted OBJECT-TYPE
	SYNTAX Counter64
	MAX-ACCESS read-only
	STATUS	 deprecated
	DESCRIPTION
		"Deprecated! The total number of accepted connections."
	::= { ltmSpdyProfileStatEntry 2 }

ltmSpdyProfileStatConnectionsCurrent OBJECT-TYPE
	SYNTAX Counter64
	MAX-ACCESS read-only
	STATUS	 deprecated
	DESCRIPTION
		"Deprecated! The total number of connections currently active."
	::= { ltmSpdyProfileStatEntry 3 }

ltmSpdyProfileStatConnectionsMax OBJECT-TYPE
	SYNTAX Counter64
	MAX-ACCESS read-only
	STATUS	 deprecated
	DESCRIPTION
		"Deprecated! The maximum number of connections open simultaneously."
	::= { ltmSpdyProfileStatEntry 4 }

ltmSpdyProfileStatDataFramesReceived OBJECT-TYPE
	SYNTAX Counter64
	MAX-ACCESS read-only
	STATUS	 deprecated
	DESCRIPTION
		"Deprecated! The total number of data frames received."
	::= { ltmSpdyProfileStatEntry 5 }

ltmSpdyProfileStatDataFramesSent OBJECT-TYPE
	SYNTAX Counter64
	MAX-ACCESS read-only
	STATUS	 deprecated
	DESCRIPTION
		"Deprecated! The total number of data frames sent."
	::= { ltmSpdyProfileStatEntry 6 }

ltmSpdyProfileStatFlowsCreated OBJECT-TYPE
	SYNTAX Counter64
	MAX-ACCESS read-only
	STATUS	 deprecated
	DESCRIPTION
		"Deprecated! The total number of flows created."
	::= { ltmSpdyProfileStatEntry 7 }

ltmSpdyProfileStatFlowsCurrent OBJECT-TYPE
	SYNTAX Counter64
	MAX-ACCESS read-only
	STATUS	 deprecated
	DESCRIPTION
		"Deprecated! The total number of flows currently active."
	::= { ltmSpdyProfileStatEntry 8 }

ltmSpdyProfileStatFlowsMax OBJECT-TYPE
	SYNTAX Counter64
	MAX-ACCESS read-only
	STATUS	 deprecated
	DESCRIPTION
		"Deprecated! The maximum number of flows open simultaneously."
	::= { ltmSpdyProfileStatEntry 9 }

ltmSpdyProfileStatGoawayFramesReceived OBJECT-TYPE
	SYNTAX Counter64
	MAX-ACCESS read-only
	STATUS	 deprecated
	DESCRIPTION
		"Deprecated! The total number of GOAWAY frames received."
	::= { ltmSpdyProfileStatEntry 10 }

ltmSpdyProfileStatGoawayFramesSent OBJECT-TYPE
	SYNTAX Counter64
	MAX-ACCESS read-only
	STATUS	 deprecated
	DESCRIPTION
		"Deprecated! The total number of GOAWAY frames sent."
	::= { ltmSpdyProfileStatEntry 11 }

ltmSpdyProfileStatHeadersFramesReceived OBJECT-TYPE
	SYNTAX Counter64
	MAX-ACCESS read-only
	STATUS	 deprecated
	DESCRIPTION
		"Deprecated! The total number of HEADERS frames received."
	::= { ltmSpdyProfileStatEntry 12 }

ltmSpdyProfileStatHeadersFramesSent OBJECT-TYPE
	SYNTAX Counter64
	MAX-ACCESS read-only
	STATUS	 deprecated
	DESCRIPTION
		"Deprecated! The total number of HEADERS frames sent."
	::= { ltmSpdyProfileStatEntry 13 }

ltmSpdyProfileStatHttpRequestBytes OBJECT-TYPE
	SYNTAX Counter64
	MAX-ACCESS read-only
	STATUS	 deprecated
	DESCRIPTION
		"Deprecated! The total number of HTTP request bytes."
	::= { ltmSpdyProfileStatEntry 14 }

ltmSpdyProfileStatHttpResponseBytes OBJECT-TYPE
	SYNTAX Counter64
	MAX-ACCESS read-only
	STATUS	 deprecated
	DESCRIPTION
		"Deprecated! The total number of HTTP response bytes."
	::= { ltmSpdyProfileStatEntry 15 }

ltmSpdyProfileStatNoopFramesReceived OBJECT-TYPE
	SYNTAX Counter64
	MAX-ACCESS read-only
	STATUS	 deprecated
	DESCRIPTION
		"Deprecated! The total number of NOOP frames received."
	::= { ltmSpdyProfileStatEntry 16 }

ltmSpdyProfileStatNoopFramesSent OBJECT-TYPE
	SYNTAX Counter64
	MAX-ACCESS read-only
	STATUS	 deprecated
	DESCRIPTION
		"Deprecated! The total number of NOOP frames sent."
	::= { ltmSpdyProfileStatEntry 17 }

ltmSpdyProfileStatPingFramesReceived OBJECT-TYPE
	SYNTAX Counter64
	MAX-ACCESS read-only
	STATUS	 deprecated
	DESCRIPTION
		"Deprecated! The total number of PING frames received."
	::= { ltmSpdyProfileStatEntry 18 }

ltmSpdyProfileStatPingFramesSent OBJECT-TYPE
	SYNTAX Counter64
	MAX-ACCESS read-only
	STATUS	 deprecated
	DESCRIPTION
		"Deprecated! The total number of PING frames sent."
	::= { ltmSpdyProfileStatEntry 19 }

ltmSpdyProfileStatRstStreamFramesReceived OBJECT-TYPE
	SYNTAX Counter64
	MAX-ACCESS read-only
	STATUS	 deprecated
	DESCRIPTION
		"Deprecated! The total number of RST_STREAM frames received."
	::= { ltmSpdyProfileStatEntry 20 }

ltmSpdyProfileStatRstStreamFramesSent OBJECT-TYPE
	SYNTAX Counter64
	MAX-ACCESS read-only
	STATUS	 deprecated
	DESCRIPTION
		"Deprecated! The total number of RST_STREAM frames sent."
	::= { ltmSpdyProfileStatEntry 21 }

ltmSpdyProfileStatSettingsFramesReceived OBJECT-TYPE
	SYNTAX Counter64
	MAX-ACCESS read-only
	STATUS	 deprecated
	DESCRIPTION
		"Deprecated! The total number of SETTINGS frames received."
	::= { ltmSpdyProfileStatEntry 22 }

ltmSpdyProfileStatSettingsFramesSent OBJECT-TYPE
	SYNTAX Counter64
	MAX-ACCESS read-only
	STATUS	 deprecated
	DESCRIPTION
		"Deprecated! The total number of SETTINGS frames sent."
	::= { ltmSpdyProfileStatEntry 23 }

ltmSpdyProfileStatSpdyRequestBytes OBJECT-TYPE
	SYNTAX Counter64
	MAX-ACCESS read-only
	STATUS	 deprecated
	DESCRIPTION
		"Deprecated! The total number of SPDY request bytes."
	::= { ltmSpdyProfileStatEntry 24 }

ltmSpdyProfileStatSpdyRequestFrames OBJECT-TYPE
	SYNTAX Counter64
	MAX-ACCESS read-only
	STATUS	 deprecated
	DESCRIPTION
		"Deprecated! The total number of SPDY request frames."
	::= { ltmSpdyProfileStatEntry 25 }

ltmSpdyProfileStatSpdyResponseBytes OBJECT-TYPE
	SYNTAX Counter64
	MAX-ACCESS read-only
	STATUS	 deprecated
	DESCRIPTION
		"Deprecated! The total number of SPDY response bytes."
	::= { ltmSpdyProfileStatEntry 26 }

ltmSpdyProfileStatSpdyResponseFrames OBJECT-TYPE
	SYNTAX Counter64
	MAX-ACCESS read-only
	STATUS	 deprecated
	DESCRIPTION
		"Deprecated! The total number of SPDY response frames."
	::= { ltmSpdyProfileStatEntry 27 }

ltmSpdyProfileStatSynReplyFramesReceived OBJECT-TYPE
	SYNTAX Counter64
	MAX-ACCESS read-only
	STATUS	 deprecated
	DESCRIPTION
		"Deprecated! The total number of SYN_REPLY frames received."
	::= { ltmSpdyProfileStatEntry 28 }

ltmSpdyProfileStatSynReplyFramesSent OBJECT-TYPE
	SYNTAX Counter64
	MAX-ACCESS read-only
	STATUS	 deprecated
	DESCRIPTION
		"Deprecated! The total number of SYN_REPLY frames sent."
	::= { ltmSpdyProfileStatEntry 29 }

ltmSpdyProfileStatSynStreamFramesReceived OBJECT-TYPE
	SYNTAX Counter64
	MAX-ACCESS read-only
	STATUS	 deprecated
	DESCRIPTION
		"Deprecated! The total number of SYN_STREAM frames received."
	::= { ltmSpdyProfileStatEntry 30 }

ltmSpdyProfileStatSynStreamFramesSent OBJECT-TYPE
	SYNTAX Counter64
	MAX-ACCESS read-only
	STATUS	 deprecated
	DESCRIPTION
		"Deprecated! The total number of SYN_STREAM frames sent."
	::= { ltmSpdyProfileStatEntry 31 }

ltmSpdyProfileStatV2StreamsCreated OBJECT-TYPE
	SYNTAX Counter64
	MAX-ACCESS read-only
	STATUS	 deprecated
	DESCRIPTION
		"Deprecated! The total number of SPDYv2 streams created."
	::= { ltmSpdyProfileStatEntry 32 }

ltmSpdyProfileStatV2StreamsCurrent OBJECT-TYPE
	SYNTAX Counter64
	MAX-ACCESS read-only
	STATUS	 deprecated
	DESCRIPTION
		"Deprecated! The total number of SPDYv2 streams currently active."
	::= { ltmSpdyProfileStatEntry 33 }

ltmSpdyProfileStatV2StreamsMax OBJECT-TYPE
	SYNTAX Counter64
	MAX-ACCESS read-only
	STATUS	 deprecated
	DESCRIPTION
		"Deprecated! The maximum number of SPDYv2 streams open simultaneously."
	::= { ltmSpdyProfileStatEntry 34 }

ltmSpdyProfileStatV3StreamsCreated OBJECT-TYPE
	SYNTAX Counter64
	MAX-ACCESS read-only
	STATUS	 deprecated
	DESCRIPTION
		"Deprecated! The total number of SPDYv3 streams created."
	::= { ltmSpdyProfileStatEntry 35 }

ltmSpdyProfileStatV3StreamsCurrent OBJECT-TYPE
	SYNTAX Counter64
	MAX-ACCESS read-only
	STATUS	 deprecated
	DESCRIPTION
		"Deprecated! The total number of SPDYv3 streams currently active."
	::= { ltmSpdyProfileStatEntry 36 }

ltmSpdyProfileStatV3StreamsMax OBJECT-TYPE
	SYNTAX Counter64
	MAX-ACCESS read-only
	STATUS	 deprecated
	DESCRIPTION
		"Deprecated! The maximum number of SPDYv3 streams open simultaneously."
	::= { ltmSpdyProfileStatEntry 37 }

ltmSpdyProfileStatWindowUpdateFramesReceived OBJECT-TYPE
	SYNTAX Counter64
	MAX-ACCESS read-only
	STATUS	 deprecated
	DESCRIPTION
		"Deprecated! The total number of WINDOW_UPDATE frames received."
	::= { ltmSpdyProfileStatEntry 38 }

ltmSpdyProfileStatWindowUpdateFramesSent OBJECT-TYPE
	SYNTAX Counter64
	MAX-ACCESS read-only
	STATUS	 deprecated
	DESCRIPTION
		"Deprecated! The total number of WINDOW_UPDATE frames sent."
	::= { ltmSpdyProfileStatEntry 39 }

--==================================================================
-- Profile_ftp_stat
--==================================================================
ltmFtpProfileStatResetStats OBJECT-TYPE
	SYNTAX INTEGER
	MAX-ACCESS read-write
	STATUS current
	DESCRIPTION
		"The action to reset resettable statistics data in ltmFtpProfileStat.
		 Setting this value to 1 will reset statistics data.
		 Note, some statistics data may not be reset including data that are incremental counters."
	::= { ltmFtpProfileStat 1 }

ltmFtpProfileStatNumber OBJECT-TYPE
	SYNTAX INTEGER
	MAX-ACCESS read-only
	STATUS current
	DESCRIPTION
		"The number of ltmFtpProfileStat entries in the table."
	::= { ltmFtpProfileStat 2 }

ltmFtpProfileStatTable OBJECT-TYPE
	SYNTAX SEQUENCE OF LtmFtpProfileStatEntry
	MAX-ACCESS not-accessible
	STATUS current
	DESCRIPTION
		"A table containing statistics information about the FTP profile."
	::= { ltmFtpProfileStat 3 }

ltmFtpProfileStatEntry OBJECT-TYPE
	SYNTAX  LtmFtpProfileStatEntry
	MAX-ACCESS not-accessible
	STATUS current
	DESCRIPTION
		"Columns in the ltmFtpProfileStat Table"
	INDEX {
		ltmFtpProfileStatName
	}
	::= { ltmFtpProfileStatTable 1 }

LtmFtpProfileStatEntry ::=
	SEQUENCE {
        	ltmFtpProfileStatName                                     LongDisplayString,
        	ltmFtpProfileStatLoginRequests                            Counter64,
        	ltmFtpProfileStatDownloadRequests                         Counter64,
        	ltmFtpProfileStatUploadRequests                           Counter64,
        	ltmFtpProfileStatFtpsSessions                             Counter64,
        	ltmFtpProfileStatPassthruTransitions                      Counter64,
        	ltmFtpProfileStatFtpsIntercepts                           Counter64,
        	ltmFtpProfileStatFtpsResets                               Counter64,
        	ltmFtpProfileStatFtpsBypasses                             Counter64,
        	ltmFtpProfileStatPassiveRequests                          Counter64,
        	ltmFtpProfileStatActiveRequests                           Counter64
	}

ltmFtpProfileStatName OBJECT-TYPE
	SYNTAX LongDisplayString
	MAX-ACCESS read-only
	STATUS current
	DESCRIPTION
		"The name of the FTP profile."
	::= { ltmFtpProfileStatEntry 1 }

ltmFtpProfileStatLoginRequests OBJECT-TYPE
	SYNTAX Counter64
	MAX-ACCESS read-only
	STATUS current
	DESCRIPTION
		"The total number of login requests received."
	::= { ltmFtpProfileStatEntry 2 }

ltmFtpProfileStatDownloadRequests OBJECT-TYPE
	SYNTAX Counter64
	MAX-ACCESS read-only
	STATUS current
	DESCRIPTION
		"The total number of download requests received."
	::= { ltmFtpProfileStatEntry 3 }

ltmFtpProfileStatUploadRequests OBJECT-TYPE
	SYNTAX Counter64
	MAX-ACCESS read-only
	STATUS current
	DESCRIPTION
		"The total number of upload requests received."
	::= { ltmFtpProfileStatEntry 4 }

ltmFtpProfileStatFtpsSessions OBJECT-TYPE
	SYNTAX Counter64
	MAX-ACCESS read-only
	STATUS current
	DESCRIPTION
		"The total number of sessions entering explicit FTPS mode."
	::= { ltmFtpProfileStatEntry 5 }

ltmFtpProfileStatPassthruTransitions OBJECT-TYPE
	SYNTAX Counter64
	MAX-ACCESS read-only
	STATUS current
	DESCRIPTION
		"The total number of sessions entering pass through mode."
	::= { ltmFtpProfileStatEntry 6 }

ltmFtpProfileStatFtpsIntercepts OBJECT-TYPE
	SYNTAX Counter64
	MAX-ACCESS read-only
	STATUS current
	DESCRIPTION
		"The total number of intercepted FTPS connections."
	::= { ltmFtpProfileStatEntry 7 }

ltmFtpProfileStatFtpsResets OBJECT-TYPE
	SYNTAX Counter64
	MAX-ACCESS read-only
	STATUS current
	DESCRIPTION
		"The total number of reset FTP connections due to FTPS policy."
	::= { ltmFtpProfileStatEntry 8 }

ltmFtpProfileStatFtpsBypasses OBJECT-TYPE
	SYNTAX Counter64
	MAX-ACCESS read-only
	STATUS current
	DESCRIPTION
		"The total number of FTP transitions to pass through mode due to SSL bypass."
	::= { ltmFtpProfileStatEntry 9 }

ltmFtpProfileStatPassiveRequests OBJECT-TYPE
	SYNTAX Counter64
	MAX-ACCESS read-only
	STATUS current
	DESCRIPTION
		"The total number of passive transfer requests received."
	::= { ltmFtpProfileStatEntry 10 }

ltmFtpProfileStatActiveRequests OBJECT-TYPE
	SYNTAX Counter64
	MAX-ACCESS read-only
	STATUS current
	DESCRIPTION
		"The total number of active transfer requests received."
	::= { ltmFtpProfileStatEntry 11 }

--==================================================================
-- Dos_application_heavy_url_includes
--==================================================================
ltmDosApplicationHeavyUrlInclNumber OBJECT-TYPE
	SYNTAX INTEGER
	MAX-ACCESS read-only
	STATUS current
	DESCRIPTION
		"The number of ltmDosApplicationHeavyUrlIncl entries in the table."
	::= { ltmDosApplicationHeavyUrlIncl 1 }

ltmDosApplicationHeavyUrlInclTable OBJECT-TYPE
	SYNTAX SEQUENCE OF LtmDosApplicationHeavyUrlInclEntry
	MAX-ACCESS not-accessible
	STATUS current
	DESCRIPTION
		"A table containing information of manually-configured (included) heavy URLs in DoS profile Application Security."
	::= { ltmDosApplicationHeavyUrlIncl 2 }

ltmDosApplicationHeavyUrlInclEntry OBJECT-TYPE
	SYNTAX  LtmDosApplicationHeavyUrlInclEntry
	MAX-ACCESS not-accessible
	STATUS current
	DESCRIPTION
		"Columns in the ltmDosApplicationHeavyUrlIncl Table"
	INDEX {
		ltmDosApplicationHeavyUrlInclProfileName,
		ltmDosApplicationHeavyUrlInclName,
		ltmDosApplicationHeavyUrlInclIndex
	}
	::= { ltmDosApplicationHeavyUrlInclTable 1 }

LtmDosApplicationHeavyUrlInclEntry ::=
	SEQUENCE {
        	ltmDosApplicationHeavyUrlInclProfileName                  LongDisplayString,
        	ltmDosApplicationHeavyUrlInclName                         LongDisplayString,
        	ltmDosApplicationHeavyUrlInclIndex                        INTEGER,
        	ltmDosApplicationHeavyUrlInclUrl                          LongDisplayString
	}

ltmDosApplicationHeavyUrlInclProfileName OBJECT-TYPE
	SYNTAX LongDisplayString
	MAX-ACCESS read-only
	STATUS current
	DESCRIPTION
		"The name of a DoS profile."
	::= { ltmDosApplicationHeavyUrlInclEntry 1 }

ltmDosApplicationHeavyUrlInclName OBJECT-TYPE
	SYNTAX LongDisplayString
	MAX-ACCESS read-only
	STATUS current
	DESCRIPTION
		"The dummy name of enabled Application Security on this profile."
	::= { ltmDosApplicationHeavyUrlInclEntry 2 }

ltmDosApplicationHeavyUrlInclIndex OBJECT-TYPE
	SYNTAX INTEGER(0..2147483647)
	MAX-ACCESS read-only
	STATUS current
	DESCRIPTION
		"The index of the included heavy URL for the specified DoS profile with Application Security."
	::= { ltmDosApplicationHeavyUrlInclEntry 3 }

ltmDosApplicationHeavyUrlInclUrl OBJECT-TYPE
	SYNTAX LongDisplayString
	MAX-ACCESS read-only
	STATUS current
	DESCRIPTION
		"The included heavy URL for the specified DoS profile with Application Security."
	::= { ltmDosApplicationHeavyUrlInclEntry 4 }

--==================================================================
-- Dos_application_heavy_url_excludes
--==================================================================
ltmDosApplicationHeavyUrlExclNumber OBJECT-TYPE
	SYNTAX INTEGER
	MAX-ACCESS read-only
	STATUS current
	DESCRIPTION
		"The number of ltmDosApplicationHeavyUrlExcl entries in the table."
	::= { ltmDosApplicationHeavyUrlExcl 1 }

ltmDosApplicationHeavyUrlExclTable OBJECT-TYPE
	SYNTAX SEQUENCE OF LtmDosApplicationHeavyUrlExclEntry
	MAX-ACCESS not-accessible
	STATUS current
	DESCRIPTION
		"A table containing information of ignored (excluded) heavy URLs in DoS profile Application Security."
	::= { ltmDosApplicationHeavyUrlExcl 2 }

ltmDosApplicationHeavyUrlExclEntry OBJECT-TYPE
	SYNTAX  LtmDosApplicationHeavyUrlExclEntry
	MAX-ACCESS not-accessible
	STATUS current
	DESCRIPTION
		"Columns in the ltmDosApplicationHeavyUrlExcl Table"
	INDEX {
		ltmDosApplicationHeavyUrlExclProfileName,
		ltmDosApplicationHeavyUrlExclName,
		ltmDosApplicationHeavyUrlExclIndex
	}
	::= { ltmDosApplicationHeavyUrlExclTable 1 }

LtmDosApplicationHeavyUrlExclEntry ::=
	SEQUENCE {
        	ltmDosApplicationHeavyUrlExclProfileName                  LongDisplayString,
        	ltmDosApplicationHeavyUrlExclName                         LongDisplayString,
        	ltmDosApplicationHeavyUrlExclIndex                        INTEGER,
        	ltmDosApplicationHeavyUrlExclUrl                          LongDisplayString
	}

ltmDosApplicationHeavyUrlExclProfileName OBJECT-TYPE
	SYNTAX LongDisplayString
	MAX-ACCESS read-only
	STATUS current
	DESCRIPTION
		"The name of a DoS profile."
	::= { ltmDosApplicationHeavyUrlExclEntry 1 }

ltmDosApplicationHeavyUrlExclName OBJECT-TYPE
	SYNTAX LongDisplayString
	MAX-ACCESS read-only
	STATUS current
	DESCRIPTION
		"The dummy name of enabled Application Security on this profile."
	::= { ltmDosApplicationHeavyUrlExclEntry 2 }

ltmDosApplicationHeavyUrlExclIndex OBJECT-TYPE
	SYNTAX INTEGER(0..2147483647)
	MAX-ACCESS read-only
	STATUS current
	DESCRIPTION
		"The index of the excluded heavy URL for the specified DoS profile with Application Security."
	::= { ltmDosApplicationHeavyUrlExclEntry 3 }

ltmDosApplicationHeavyUrlExclUrl OBJECT-TYPE
	SYNTAX LongDisplayString
	MAX-ACCESS read-only
	STATUS current
	DESCRIPTION
		"The excluded heavy URL for the specified DoS profile with Application Security."
	::= { ltmDosApplicationHeavyUrlExclEntry 4 }

--==================================================================
-- Profile_v6rd
--==================================================================
ltmV6rdProfileNumber OBJECT-TYPE
	SYNTAX INTEGER
	MAX-ACCESS read-only
	STATUS current
	DESCRIPTION
		"The number of ltmV6rdProfile entries in the table."
	::= { ltmV6rdProfile 1 }

ltmV6rdProfileTable OBJECT-TYPE
	SYNTAX SEQUENCE OF LtmV6rdProfileEntry
	MAX-ACCESS not-accessible
	STATUS current
	DESCRIPTION
		"A table containing information about the V6RD profile."
	::= { ltmV6rdProfile 2 }

ltmV6rdProfileEntry OBJECT-TYPE
	SYNTAX  LtmV6rdProfileEntry
	MAX-ACCESS not-accessible
	STATUS current
	DESCRIPTION
		"Columns in the ltmV6rdProfile Table"
	INDEX {
		ltmV6rdProfileName
	}
	::= { ltmV6rdProfileTable 1 }

LtmV6rdProfileEntry ::=
	SEQUENCE {
        	ltmV6rdProfileName                                        LongDisplayString,
        	ltmV6rdProfileConfigSource                                INTEGER,
        	ltmV6rdProfileDefaultName                                 LongDisplayString,
        	ltmV6rdProfileIpv4prefixType                              InetAddressType,
        	ltmV6rdProfileIpv4prefix                                  InetAddress,
        	ltmV6rdProfileIpv4prefixlen                               Gauge,
        	ltmV6rdProfileV6rdprefixType                              InetAddressType,
        	ltmV6rdProfileV6rdprefix                                  InetAddress,
        	ltmV6rdProfileV6rdprefixlen                               Gauge
	}

ltmV6rdProfileName OBJECT-TYPE
	SYNTAX LongDisplayString
	MAX-ACCESS read-only
	STATUS current
	DESCRIPTION
		"The name of a V6RD profile."
	::= { ltmV6rdProfileEntry 1 }

ltmV6rdProfileConfigSource OBJECT-TYPE
	SYNTAX INTEGER {
		usercfg(0),
		basecfg(1)
	}
	MAX-ACCESS read-only
	STATUS current
	DESCRIPTION
		"The state that specifies whether this is a base/pre-configured profile
	   or user defined profile."
	::= { ltmV6rdProfileEntry 2 }

ltmV6rdProfileDefaultName OBJECT-TYPE
	SYNTAX LongDisplayString
	MAX-ACCESS read-only
	STATUS current
	DESCRIPTION
		"The name of the profile from which the specified profile derives
	   its attribute default values."
	::= { ltmV6rdProfileEntry 3 }

ltmV6rdProfileIpv4prefixType OBJECT-TYPE
	SYNTAX InetAddressType
	MAX-ACCESS read-only
	STATUS current
	DESCRIPTION
		"The IP address type of ltmV6rdProfileIpv4prefix."
	::= { ltmV6rdProfileEntry 4 }

ltmV6rdProfileIpv4prefix OBJECT-TYPE
	SYNTAX InetAddress
	MAX-ACCESS read-only
	STATUS current
	DESCRIPTION
		"IPv4 prefix for Customer Edge routers. It is interpreted within
	        the context of a ltmV6rdProfileIpv4prefixType value."
	::= { ltmV6rdProfileEntry 5 }

ltmV6rdProfileIpv4prefixlen OBJECT-TYPE
	SYNTAX Gauge
	MAX-ACCESS read-only
	STATUS current
	DESCRIPTION
		"The number of high-order bits of IPv4 addresses that are not embedded in the IPv6 addresses of a given V6RD domain."
	::= { ltmV6rdProfileEntry 6 }

ltmV6rdProfileV6rdprefixType OBJECT-TYPE
	SYNTAX InetAddressType
	MAX-ACCESS read-only
	STATUS current
	DESCRIPTION
		"The IP address type of ltmV6rdProfileV6rdprefix."
	::= { ltmV6rdProfileEntry 7 }

ltmV6rdProfileV6rdprefix OBJECT-TYPE
	SYNTAX InetAddress
	MAX-ACCESS read-only
	STATUS current
	DESCRIPTION
		"IPv6 prefix 6RD domain. It is interpreted within
	        the context of a ltmV6rdProfileV6rdprefixType value."
	::= { ltmV6rdProfileEntry 8 }

ltmV6rdProfileV6rdprefixlen OBJECT-TYPE
	SYNTAX Gauge
	MAX-ACCESS read-only
	STATUS current
	DESCRIPTION
		"The length of the 6rd IPv6 prefix for the given 6rd domain."
	::= { ltmV6rdProfileEntry 9 }

--==================================================================
-- Profile_pptp
--==================================================================
ltmPptpProfileNumber OBJECT-TYPE
	SYNTAX INTEGER
	MAX-ACCESS read-only
	STATUS current
	DESCRIPTION
		"The number of ltmPptpProfile entries in the table."
	::= { ltmPptpProfile 1 }

ltmPptpProfileTable OBJECT-TYPE
	SYNTAX SEQUENCE OF LtmPptpProfileEntry
	MAX-ACCESS not-accessible
	STATUS current
	DESCRIPTION
		"A table containing information about the PPTP profile."
	::= { ltmPptpProfile 2 }

ltmPptpProfileEntry OBJECT-TYPE
	SYNTAX  LtmPptpProfileEntry
	MAX-ACCESS not-accessible
	STATUS current
	DESCRIPTION
		"Columns in the ltmPptpProfile Table"
	INDEX {
		ltmPptpProfileName
	}
	::= { ltmPptpProfileTable 1 }

LtmPptpProfileEntry ::=
	SEQUENCE {
        	ltmPptpProfileName                                        LongDisplayString,
        	ltmPptpProfileDescription                                 LongDisplayString,
        	ltmPptpProfileConfigSource                                INTEGER,
        	ltmPptpProfileDefaultName                                 LongDisplayString,
        	ltmPptpProfileLogServerIp                                 INTEGER,
        	ltmPptpProfileLogPublisher                                LongDisplayString,
        	ltmPptpProfileCsvFormat                                   INTEGER
	}

ltmPptpProfileName OBJECT-TYPE
	SYNTAX LongDisplayString
	MAX-ACCESS read-only
	STATUS current
	DESCRIPTION
		"The name of a PPTP profile."
	::= { ltmPptpProfileEntry 1 }

ltmPptpProfileDescription OBJECT-TYPE
	SYNTAX LongDisplayString
	MAX-ACCESS read-only
	STATUS current
	DESCRIPTION
		"The description of a PPTP profile."
	::= { ltmPptpProfileEntry 2 }

ltmPptpProfileConfigSource OBJECT-TYPE
	SYNTAX INTEGER {
		usercfg(0),
		basecfg(1)
	}
	MAX-ACCESS read-only
	STATUS current
	DESCRIPTION
		"The state that specifies whether this is a base/pre-configured profile
	    or user defined profile."
	::= { ltmPptpProfileEntry 3 }

ltmPptpProfileDefaultName OBJECT-TYPE
	SYNTAX LongDisplayString
	MAX-ACCESS read-only
	STATUS current
	DESCRIPTION
		"The name of the profile from which the specified profile derives
	    its attribute default values."
	::= { ltmPptpProfileEntry 4 }

ltmPptpProfileLogServerIp OBJECT-TYPE
	SYNTAX INTEGER {
		false(0),
		true(1)
	}
	MAX-ACCESS read-only
	STATUS current
	DESCRIPTION
		"state indicate whether the log messages for call establishment/disconnect
	    include the server's ip address."
	::= { ltmPptpProfileEntry 5 }

ltmPptpProfileLogPublisher OBJECT-TYPE
	SYNTAX LongDisplayString
	MAX-ACCESS read-only
	STATUS current
	DESCRIPTION
		"Specifies the name of the log publisher for PPTP events."
	::= { ltmPptpProfileEntry 6 }

ltmPptpProfileCsvFormat OBJECT-TYPE
	SYNTAX INTEGER {
		false(0),
		true(1)
	}
	MAX-ACCESS read-only
	STATUS current
	DESCRIPTION
		"Use csv log format for output."
	::= { ltmPptpProfileEntry 7 }

--==================================================================
-- Profile_pptp_stat
--==================================================================
ltmPptpProfileStatResetStats OBJECT-TYPE
	SYNTAX INTEGER
	MAX-ACCESS read-write
	STATUS current
	DESCRIPTION
		"The action to reset resettable statistics data in ltmPptpProfileStat.
		 Setting this value to 1 will reset statistics data.
		 Note, some statistics data may not be reset including data that are incremental counters."
	::= { ltmPptpProfileStat 1 }

ltmPptpProfileStatNumber OBJECT-TYPE
	SYNTAX INTEGER
	MAX-ACCESS read-only
	STATUS current
	DESCRIPTION
		"The number of ltmPptpProfileStat entries in the table."
	::= { ltmPptpProfileStat 2 }

ltmPptpProfileStatTable OBJECT-TYPE
	SYNTAX SEQUENCE OF LtmPptpProfileStatEntry
	MAX-ACCESS not-accessible
	STATUS current
	DESCRIPTION
		"A table containing statistics information about the PPTP profile."
	::= { ltmPptpProfileStat 3 }

ltmPptpProfileStatEntry OBJECT-TYPE
	SYNTAX  LtmPptpProfileStatEntry
	MAX-ACCESS not-accessible
	STATUS current
	DESCRIPTION
		"Columns in the ltmPptpProfileStat Table"
	INDEX {
		ltmPptpProfileStatName
	}
	::= { ltmPptpProfileStatTable 1 }

LtmPptpProfileStatEntry ::=
	SEQUENCE {
        	ltmPptpProfileStatName                                    LongDisplayString,
        	ltmPptpProfileStatStartRequests                           Counter64,
        	ltmPptpProfileStatStartReplies                            Counter64,
        	ltmPptpProfileStatStopRequests                            Counter64,
        	ltmPptpProfileStatStopReplies                             Counter64,
        	ltmPptpProfileStatEchoRequests                            Counter64,
        	ltmPptpProfileStatEchoReplies                             Counter64,
        	ltmPptpProfileStatOutgoingCallRequests                    Counter64,
        	ltmPptpProfileStatOutgoingCallReplies                     Counter64,
        	ltmPptpProfileStatCallClearRequests                       Counter64,
        	ltmPptpProfileStatCallDisconnectNotifies                  Counter64,
        	ltmPptpProfileStatWanErrorNotifies                        Counter64,
        	ltmPptpProfileStatSetLinkInfo                             Counter64,
        	ltmPptpProfileStatActiveCalls                             Counter64,
        	ltmPptpProfileStatTotalCalls                              Counter64,
        	ltmPptpProfileStatFailedCalls                             Counter64
	}

ltmPptpProfileStatName OBJECT-TYPE
	SYNTAX LongDisplayString
	MAX-ACCESS read-only
	STATUS current
	DESCRIPTION
		"The name of the PPTP profile."
	::= { ltmPptpProfileStatEntry 1 }

ltmPptpProfileStatStartRequests OBJECT-TYPE
	SYNTAX Counter64
	MAX-ACCESS read-only
	STATUS current
	DESCRIPTION
		"Number of PPTP control messages used to establish the control
	     connection between a server and a client."
	::= { ltmPptpProfileStatEntry 2 }

ltmPptpProfileStatStartReplies OBJECT-TYPE
	SYNTAX Counter64
	MAX-ACCESS read-only
	STATUS current
	DESCRIPTION
		"Number of PPTP control messages sent in reply to a received
	     Start-Control-Connection-Request message."
	::= { ltmPptpProfileStatEntry 3 }

ltmPptpProfileStatStopRequests OBJECT-TYPE
	SYNTAX Counter64
	MAX-ACCESS read-only
	STATUS current
	DESCRIPTION
		"Number of PPTP control messages sent by one peer of a client-server
	     control connection to inform the other peer that the control
	     connection should be closed."
	::= { ltmPptpProfileStatEntry 4 }

ltmPptpProfileStatStopReplies OBJECT-TYPE
	SYNTAX Counter64
	MAX-ACCESS read-only
	STATUS current
	DESCRIPTION
		"Number of PPTP control messages sent by one peer of a client-server
	     control connection upon receipt of a
	     Stop-Control-Connection-Request from the other peer."
	::= { ltmPptpProfileStatEntry 5 }

ltmPptpProfileStatEchoRequests OBJECT-TYPE
	SYNTAX Counter64
	MAX-ACCESS read-only
	STATUS current
	DESCRIPTION
		"Number of PPTP control messages sent by either peer of a client-server
	     control connection."
	::= { ltmPptpProfileStatEntry 6 }

ltmPptpProfileStatEchoReplies OBJECT-TYPE
	SYNTAX Counter64
	MAX-ACCESS read-only
	STATUS current
	DESCRIPTION
		"Number of PPTP control messages sent by either peer of a client-server
	     control connection in response to the receipt of an Echo-Request."
	::= { ltmPptpProfileStatEntry 7 }

ltmPptpProfileStatOutgoingCallRequests OBJECT-TYPE
	SYNTAX Counter64
	MAX-ACCESS read-only
	STATUS current
	DESCRIPTION
		"Number of PPTP control messages sent by the server to the client to
	     indicate that an outbound call from the client is to be
	     established."
	::= { ltmPptpProfileStatEntry 8 }

ltmPptpProfileStatOutgoingCallReplies OBJECT-TYPE
	SYNTAX Counter64
	MAX-ACCESS read-only
	STATUS current
	DESCRIPTION
		"Number of PPTP control messages sent by the client to the server in
	     response to a received Outgoing-Call-Request message."
	::= { ltmPptpProfileStatEntry 9 }

ltmPptpProfileStatCallClearRequests OBJECT-TYPE
	SYNTAX Counter64
	MAX-ACCESS read-only
	STATUS current
	DESCRIPTION
		"Number of PPTP control messages sent by the server to the client
	     indicating that a particular call is to be disconnected."
	::= { ltmPptpProfileStatEntry 10 }

ltmPptpProfileStatCallDisconnectNotifies OBJECT-TYPE
	SYNTAX Counter64
	MAX-ACCESS read-only
	STATUS current
	DESCRIPTION
		"Number of PPTP Call-Disconnect-Notify control messages sent by the client
	    to the server.  Its purpose is to inform the server of both the
	    disconnection and the reason for it."
	::= { ltmPptpProfileStatEntry 11 }

ltmPptpProfileStatWanErrorNotifies OBJECT-TYPE
	SYNTAX Counter64
	MAX-ACCESS read-only
	STATUS current
	DESCRIPTION
		"Number of WAN-Error-Notify messages sent by the client to the server to
	    indicate WAN error conditions (conditions that occur on the interface
	    supporting PPP)."
	::= { ltmPptpProfileStatEntry 12 }

ltmPptpProfileStatSetLinkInfo OBJECT-TYPE
	SYNTAX Counter64
	MAX-ACCESS read-only
	STATUS current
	DESCRIPTION
		"Number of PPTP control messages sent by the server to the client to
	     set PPP-negotiated options."
	::= { ltmPptpProfileStatEntry 13 }

ltmPptpProfileStatActiveCalls OBJECT-TYPE
	SYNTAX Counter64
	MAX-ACCESS read-only
	STATUS current
	DESCRIPTION
		"Number of active PPTP calls."
	::= { ltmPptpProfileStatEntry 14 }

ltmPptpProfileStatTotalCalls OBJECT-TYPE
	SYNTAX Counter64
	MAX-ACCESS read-only
	STATUS current
	DESCRIPTION
		"Total number of PPTP calls served."
	::= { ltmPptpProfileStatEntry 15 }

ltmPptpProfileStatFailedCalls OBJECT-TYPE
	SYNTAX Counter64
	MAX-ACCESS read-only
	STATUS current
	DESCRIPTION
		"Total number of PPTP calls that failed."
	::= { ltmPptpProfileStatEntry 16 }

--==================================================================
-- Profile_pcp
--==================================================================
ltmPcpProfileNumber OBJECT-TYPE
	SYNTAX INTEGER
	MAX-ACCESS read-only
	STATUS current
	DESCRIPTION
		"The number of ltmPcpProfile entries in the table."
	::= { ltmPcpProfile 1 }

ltmPcpProfileTable OBJECT-TYPE
	SYNTAX SEQUENCE OF LtmPcpProfileEntry
	MAX-ACCESS not-accessible
	STATUS current
	DESCRIPTION
		"A table containing information about the Port Control Protocol (PCP) profile."
	::= { ltmPcpProfile 2 }

ltmPcpProfileEntry OBJECT-TYPE
	SYNTAX  LtmPcpProfileEntry
	MAX-ACCESS not-accessible
	STATUS current
	DESCRIPTION
		"Columns in the ltmPcpProfile Table"
	INDEX {
		ltmPcpProfileName
	}
	::= { ltmPcpProfileTable 1 }

LtmPcpProfileEntry ::=
	SEQUENCE {
        	ltmPcpProfileName                                         LongDisplayString,
        	ltmPcpProfileConfigSource                                 INTEGER,
        	ltmPcpProfileDefaultName                                  LongDisplayString,
        	ltmPcpProfileListeningPort                                InetPortNumber,
        	ltmPcpProfileMulticastPort                                InetPortNumber,
        	ltmPcpProfileMinMappingLifetime                           Gauge,
        	ltmPcpProfileMaxMappingLifetime                           Gauge,
        	ltmPcpProfileMapRecycleDelay                              Gauge,
        	ltmPcpProfileMapLimitPerClient                            Gauge,
        	ltmPcpProfileMapFilterLimit                               Gauge,
        	ltmPcpProfileThirdPartyOption                             INTEGER,
        	ltmPcpProfileRuleName                                     LongDisplayString
	}

ltmPcpProfileName OBJECT-TYPE
	SYNTAX LongDisplayString
	MAX-ACCESS read-only
	STATUS current
	DESCRIPTION
		"The name of a PCP profile."
	::= { ltmPcpProfileEntry 1 }

ltmPcpProfileConfigSource OBJECT-TYPE
	SYNTAX INTEGER {
		usercfg(0),
		basecfg(1)
	}
	MAX-ACCESS read-only
	STATUS current
	DESCRIPTION
		"The state that specifies whether this is a base/pre-configured profile
	    or user defined profile."
	::= { ltmPcpProfileEntry 2 }

ltmPcpProfileDefaultName OBJECT-TYPE
	SYNTAX LongDisplayString
	MAX-ACCESS read-only
	STATUS current
	DESCRIPTION
		"The name of the profile from which the specified profile derives
	    its attribute default values."
	::= { ltmPcpProfileEntry 3 }

ltmPcpProfileListeningPort OBJECT-TYPE
	SYNTAX InetPortNumber
	MAX-ACCESS read-only
	STATUS current
	DESCRIPTION
		"The port which Port Control Protocol listener listens for PCP client-to-server
	    request message."
	::= { ltmPcpProfileEntry 4 }

ltmPcpProfileMulticastPort OBJECT-TYPE
	SYNTAX InetPortNumber
	MAX-ACCESS read-only
	STATUS current
	DESCRIPTION
		"The port which Port Control Protocol sends server-to-client multicast notifications."
	::= { ltmPcpProfileEntry 5 }

ltmPcpProfileMinMappingLifetime OBJECT-TYPE
	SYNTAX Gauge
	MAX-ACCESS read-only
	STATUS current
	DESCRIPTION
		"Minimum duration of a mapping."
	::= { ltmPcpProfileEntry 6 }

ltmPcpProfileMaxMappingLifetime OBJECT-TYPE
	SYNTAX Gauge
	MAX-ACCESS read-only
	STATUS current
	DESCRIPTION
		"Maximum allowed duration of a mapping."
	::= { ltmPcpProfileEntry 7 }

ltmPcpProfileMapRecycleDelay OBJECT-TYPE
	SYNTAX Gauge
	MAX-ACCESS read-only
	STATUS current
	DESCRIPTION
		"How long to wait before reusing a mapping that was deleted."
	::= { ltmPcpProfileEntry 8 }

ltmPcpProfileMapLimitPerClient OBJECT-TYPE
	SYNTAX Gauge
	MAX-ACCESS read-only
	STATUS current
	DESCRIPTION
		"Maximum number of mappings allowed per client."
	::= { ltmPcpProfileEntry 9 }

ltmPcpProfileMapFilterLimit OBJECT-TYPE
	SYNTAX Gauge
	MAX-ACCESS read-only
	STATUS current
	DESCRIPTION
		"Maximum number of filters allowed per mapping."
	::= { ltmPcpProfileEntry 10 }

ltmPcpProfileThirdPartyOption OBJECT-TYPE
	SYNTAX INTEGER {
		false(0),
		true(1)
	}
	MAX-ACCESS read-only
	STATUS current
	DESCRIPTION
		"If true, allows a PCP client to create mappings on behalf of another internal host."
	::= { ltmPcpProfileEntry 11 }

ltmPcpProfileRuleName OBJECT-TYPE
	SYNTAX LongDisplayString
	MAX-ACCESS read-only
	STATUS current
	DESCRIPTION
		"The name of the rule that the specified profile will be using."
	::= { ltmPcpProfileEntry 12 }

--==================================================================
-- Pcp_prefix
--==================================================================
ltmPcpPrefixNumber OBJECT-TYPE
	SYNTAX INTEGER
	MAX-ACCESS read-only
	STATUS current
	DESCRIPTION
		"The number of ltmPcpPrefix entries in the table."
	::= { ltmPcpPrefix 1 }

ltmPcpPrefixTable OBJECT-TYPE
	SYNTAX SEQUENCE OF LtmPcpPrefixEntry
	MAX-ACCESS not-accessible
	STATUS current
	DESCRIPTION
		"A table containing information of PCP prefix."
	::= { ltmPcpPrefix 2 }

ltmPcpPrefixEntry OBJECT-TYPE
	SYNTAX  LtmPcpPrefixEntry
	MAX-ACCESS not-accessible
	STATUS current
	DESCRIPTION
		"Columns in the ltmPcpPrefix Table"
	INDEX {
		ltmPcpPrefixName
	}
	::= { ltmPcpPrefixTable 1 }

LtmPcpPrefixEntry ::=
	SEQUENCE {
        	ltmPcpPrefixName                                          LongDisplayString,
        	ltmPcpPrefixAddrType                                      InetAddressType,
        	ltmPcpPrefixAddr                                          InetAddress
	}

ltmPcpPrefixName OBJECT-TYPE
	SYNTAX LongDisplayString
	MAX-ACCESS read-only
	STATUS current
	DESCRIPTION
		"The name of a PCP prefix node."
	::= { ltmPcpPrefixEntry 1 }

ltmPcpPrefixAddrType OBJECT-TYPE
	SYNTAX InetAddressType
	MAX-ACCESS read-only
	STATUS current
	DESCRIPTION
		"The IP address type of ltmPcpPrefixAddr."
	::= { ltmPcpPrefixEntry 2 }

ltmPcpPrefixAddr OBJECT-TYPE
	SYNTAX InetAddress
	MAX-ACCESS read-only
	STATUS current
	DESCRIPTION
		"The IP address of a node. It is interpreted within
	     the context of a ltmPcpPrefixAddrType value."
	::= { ltmPcpPrefixEntry 3 }

--==================================================================
-- Pcp_prefix_profile_pcp
--==================================================================
ltmPcpPrefixProfilePcpNumber OBJECT-TYPE
	SYNTAX INTEGER
	MAX-ACCESS read-only
	STATUS current
	DESCRIPTION
		"The number of ltmPcpPrefixProfilePcp entries in the table."
	::= { ltmPcpPrefixProfilePcp 1 }

ltmPcpPrefixProfilePcpTable OBJECT-TYPE
	SYNTAX SEQUENCE OF LtmPcpPrefixProfilePcpEntry
	MAX-ACCESS not-accessible
	STATUS current
	DESCRIPTION
		"A table containing information of PCP profile prefix, or third-party-subnets."
	::= { ltmPcpPrefixProfilePcp 2 }

ltmPcpPrefixProfilePcpEntry OBJECT-TYPE
	SYNTAX  LtmPcpPrefixProfilePcpEntry
	MAX-ACCESS not-accessible
	STATUS current
	DESCRIPTION
		"Columns in the ltmPcpPrefixProfilePcp Table"
	INDEX {
		ltmPcpPrefixProfilePcpName,
		ltmPcpPrefixProfilePcpPcpPrefixName
	}
	::= { ltmPcpPrefixProfilePcpTable 1 }

LtmPcpPrefixProfilePcpEntry ::=
	SEQUENCE {
        	ltmPcpPrefixProfilePcpPcpPrefixName                       LongDisplayString,
        	ltmPcpPrefixProfilePcpName                                LongDisplayString,
        	ltmPcpPrefixProfilePcpPrefixAddressType                   InetAddressType,
        	ltmPcpPrefixProfilePcpPrefixAddress                       InetAddress
	}

ltmPcpPrefixProfilePcpPcpPrefixName OBJECT-TYPE
	SYNTAX LongDisplayString
	MAX-ACCESS read-only
	STATUS current
	DESCRIPTION
		"The name of a PCP prefix node."
	::= { ltmPcpPrefixProfilePcpEntry 1 }

ltmPcpPrefixProfilePcpName OBJECT-TYPE
	SYNTAX LongDisplayString
	MAX-ACCESS read-only
	STATUS current
	DESCRIPTION
		"The name of a PCP profile."
	::= { ltmPcpPrefixProfilePcpEntry 2 }

ltmPcpPrefixProfilePcpPrefixAddressType OBJECT-TYPE
	SYNTAX InetAddressType
	MAX-ACCESS read-only
	STATUS current
	DESCRIPTION
		"The IP address type of ltmPcpPrefixProfilePcpPrefixAddress."
	::= { ltmPcpPrefixProfilePcpEntry 3 }

ltmPcpPrefixProfilePcpPrefixAddress OBJECT-TYPE
	SYNTAX InetAddress
	MAX-ACCESS read-only
	STATUS current
	DESCRIPTION
		"The IP address of a node. It is interpreted within
	        the context of a ltmPcpPrefixProfilePcpPrefixAddressType value."
	::= { ltmPcpPrefixProfilePcpEntry 4 }

--==================================================================
-- Profile_pcp_stat
--==================================================================
ltmPcpProfileStatResetStats OBJECT-TYPE
	SYNTAX INTEGER
	MAX-ACCESS read-write
	STATUS current
	DESCRIPTION
		"The action to reset resettable statistics data in ltmPcpProfileStat.
		 Setting this value to 1 will reset statistics data.
		 Note, some statistics data may not be reset including data that are incremental counters."
	::= { ltmPcpProfileStat 1 }

ltmPcpProfileStatNumber OBJECT-TYPE
	SYNTAX INTEGER
	MAX-ACCESS read-only
	STATUS current
	DESCRIPTION
		"The number of ltmPcpProfileStat entries in the table."
	::= { ltmPcpProfileStat 2 }

ltmPcpProfileStatTable OBJECT-TYPE
	SYNTAX SEQUENCE OF LtmPcpProfileStatEntry
	MAX-ACCESS not-accessible
	STATUS current
	DESCRIPTION
		"A table containing statistics information about the Port Control Protocol
	            (PCP) profile."
	::= { ltmPcpProfileStat 3 }

ltmPcpProfileStatEntry OBJECT-TYPE
	SYNTAX  LtmPcpProfileStatEntry
	MAX-ACCESS not-accessible
	STATUS current
	DESCRIPTION
		"Columns in the ltmPcpProfileStat Table"
	INDEX {
		ltmPcpProfileStatName
	}
	::= { ltmPcpProfileStatTable 1 }

LtmPcpProfileStatEntry ::=
	SEQUENCE {
        	ltmPcpProfileStatName                                     LongDisplayString,
        	ltmPcpProfileStatPcpAnnounceRequests                      Counter64,
        	ltmPcpProfileStatPcpAnnounceResponsesUcast                Counter64,
        	ltmPcpProfileStatPcpAnnounceResponsesMulticast            Counter64,
        	ltmPcpProfileStatPcpMapRequests                           Counter64,
        	ltmPcpProfileStatPcpMapResponses                          Counter64,
        	ltmPcpProfileStatPcpPeerRequests                          Counter64,
        	ltmPcpProfileStatPcpPeerResponses                         Counter64,
        	ltmPcpProfileStatPcpErrorsInvalidRequest                  Counter64,
        	ltmPcpProfileStatPcpErrorsUnavailableResource             Counter64,
        	ltmPcpProfileStatPcpErrorsNotAuthorized                   Counter64,
        	ltmPcpProfileStatPcpErrorsOther                           Counter64
	}

ltmPcpProfileStatName OBJECT-TYPE
	SYNTAX LongDisplayString
	MAX-ACCESS read-only
	STATUS current
	DESCRIPTION
		"The name of the PCP profile."
	::= { ltmPcpProfileStatEntry 1 }

ltmPcpProfileStatPcpAnnounceRequests OBJECT-TYPE
	SYNTAX Counter64
	MAX-ACCESS read-only
	STATUS current
	DESCRIPTION
		"The total number of Announce requests received."
	::= { ltmPcpProfileStatEntry 2 }

ltmPcpProfileStatPcpAnnounceResponsesUcast OBJECT-TYPE
	SYNTAX Counter64
	MAX-ACCESS read-only
	STATUS current
	DESCRIPTION
		"The total number of unicast Announce responses transmitted."
	::= { ltmPcpProfileStatEntry 3 }

ltmPcpProfileStatPcpAnnounceResponsesMulticast OBJECT-TYPE
	SYNTAX Counter64
	MAX-ACCESS read-only
	STATUS current
	DESCRIPTION
		"The total number of multicast Announce responses transmitted."
	::= { ltmPcpProfileStatEntry 4 }

ltmPcpProfileStatPcpMapRequests OBJECT-TYPE
	SYNTAX Counter64
	MAX-ACCESS read-only
	STATUS current
	DESCRIPTION
		"The total number of Map requests received."
	::= { ltmPcpProfileStatEntry 5 }

ltmPcpProfileStatPcpMapResponses OBJECT-TYPE
	SYNTAX Counter64
	MAX-ACCESS read-only
	STATUS current
	DESCRIPTION
		"The total number of Map responses transmitted."
	::= { ltmPcpProfileStatEntry 6 }

ltmPcpProfileStatPcpPeerRequests OBJECT-TYPE
	SYNTAX Counter64
	MAX-ACCESS read-only
	STATUS current
	DESCRIPTION
		"The total number of Peer requests received."
	::= { ltmPcpProfileStatEntry 7 }

ltmPcpProfileStatPcpPeerResponses OBJECT-TYPE
	SYNTAX Counter64
	MAX-ACCESS read-only
	STATUS current
	DESCRIPTION
		"The total number of Peer responses transmitted."
	::= { ltmPcpProfileStatEntry 8 }

ltmPcpProfileStatPcpErrorsInvalidRequest OBJECT-TYPE
	SYNTAX Counter64
	MAX-ACCESS read-only
	STATUS current
	DESCRIPTION
		"The total number of invalid or malformed PCP requests received."
	::= { ltmPcpProfileStatEntry 9 }

ltmPcpProfileStatPcpErrorsUnavailableResource OBJECT-TYPE
	SYNTAX Counter64
	MAX-ACCESS read-only
	STATUS current
	DESCRIPTION
		"The total number of PCP requests received where the server has insufficient
	     resources to complete the requested operation."
	::= { ltmPcpProfileStatEntry 10 }

ltmPcpProfileStatPcpErrorsNotAuthorized OBJECT-TYPE
	SYNTAX Counter64
	MAX-ACCESS read-only
	STATUS current
	DESCRIPTION
		"The total number of PCP requests that generated (or caused) an
	    unauthorized error when attempting to create a mapping."
	::= { ltmPcpProfileStatEntry 11 }

ltmPcpProfileStatPcpErrorsOther OBJECT-TYPE
	SYNTAX Counter64
	MAX-ACCESS read-only
	STATUS current
	DESCRIPTION
		"The total number of PCP requests received that resulted in other errors."
	::= { ltmPcpProfileStatEntry 12 }

--==================================================================
-- Tmm_dns_zone_stat
--==================================================================
ltmDnsExpressStatResetStats OBJECT-TYPE
	SYNTAX INTEGER
	MAX-ACCESS read-write
	STATUS current
	DESCRIPTION
		"The action to reset resettable statistics data in ltmDnsExpressStat.
		 Setting this value to 1 will reset statistics data.
		 Note, some statistics data may not be reset including data that are incremental counters."
	::= { ltmDnsExpressStat 1 }

ltmDnsExpressStatNumber OBJECT-TYPE
	SYNTAX INTEGER
	MAX-ACCESS read-only
	STATUS current
	DESCRIPTION
		"The number of ltmDnsExpressStat entries in the table."
	::= { ltmDnsExpressStat 2 }

ltmDnsExpressStatTable OBJECT-TYPE
	SYNTAX SEQUENCE OF LtmDnsExpressStatEntry
	MAX-ACCESS not-accessible
	STATUS current
	DESCRIPTION
		"A table containing statistics information about DNS Express zone transfer."
	::= { ltmDnsExpressStat 3 }

ltmDnsExpressStatEntry OBJECT-TYPE
	SYNTAX  LtmDnsExpressStatEntry
	MAX-ACCESS not-accessible
	STATUS current
	DESCRIPTION
		"Columns in the ltmDnsExpressStat Table"
	INDEX {
		ltmDnsExpressStatName
	}
	::= { ltmDnsExpressStatTable 1 }

LtmDnsExpressStatEntry ::=
	SEQUENCE {
        	ltmDnsExpressStatName                                     LongDisplayString,
        	ltmDnsExpressStatDnsxQueries                              Counter64,
        	ltmDnsExpressStatDnsxResponses                            Counter64,
        	ltmDnsExpressStatDnsxNotifiesRecv                         Counter64,
        	ltmDnsExpressStatAxfrQueries                              Counter64,
        	ltmDnsExpressStatIxfrQueries                              Counter64,
        	ltmDnsExpressStatXfrQueriesAclFailed                      Counter64,
        	ltmDnsExpressStatXfrNotifiesSent                          Counter64,
        	ltmDnsExpressStatDnsxXfrMsgs                              Counter64,
        	ltmDnsExpressStatXfrNotifiesFailed                        Counter64,
        	ltmDnsExpressStatTsigMissing                              Counter64,
        	ltmDnsExpressStatTsigNotRequired                          Counter64,
        	ltmDnsExpressStatTsigVerified                             Counter64,
        	ltmDnsExpressStatTsigBadKey                               Counter64,
        	ltmDnsExpressStatTsigBadSig                               Counter64,
        	ltmDnsExpressStatTsigBadTime                              Counter64
	}

ltmDnsExpressStatName OBJECT-TYPE
	SYNTAX LongDisplayString
	MAX-ACCESS read-only
	STATUS current
	DESCRIPTION
		"The name of DNS zone."
	::= { ltmDnsExpressStatEntry 1 }

ltmDnsExpressStatDnsxQueries OBJECT-TYPE
	SYNTAX Counter64
	MAX-ACCESS read-only
	STATUS current
	DESCRIPTION
		"Total number of queries sent to DNS Express."
	::= { ltmDnsExpressStatEntry 2 }

ltmDnsExpressStatDnsxResponses OBJECT-TYPE
	SYNTAX Counter64
	MAX-ACCESS read-only
	STATUS current
	DESCRIPTION
		"Total number of queries answered by DNS Express."
	::= { ltmDnsExpressStatEntry 3 }

ltmDnsExpressStatDnsxNotifiesRecv OBJECT-TYPE
	SYNTAX Counter64
	MAX-ACCESS read-only
	STATUS current
	DESCRIPTION
		"Total number of zone notifies received by DNS Express."
	::= { ltmDnsExpressStatEntry 4 }

ltmDnsExpressStatAxfrQueries OBJECT-TYPE
	SYNTAX Counter64
	MAX-ACCESS read-only
	STATUS current
	DESCRIPTION
		"Total number of AXFR queries."
	::= { ltmDnsExpressStatEntry 5 }

ltmDnsExpressStatIxfrQueries OBJECT-TYPE
	SYNTAX Counter64
	MAX-ACCESS read-only
	STATUS current
	DESCRIPTION
		"Total number of IXFR queries."
	::= { ltmDnsExpressStatEntry 6 }

ltmDnsExpressStatXfrQueriesAclFailed OBJECT-TYPE
	SYNTAX Counter64
	MAX-ACCESS read-only
	STATUS current
	DESCRIPTION
		"Total number of zone transfer queries whose source IP address is not in the ACL."
	::= { ltmDnsExpressStatEntry 7 }

ltmDnsExpressStatXfrNotifiesSent OBJECT-TYPE
	SYNTAX Counter64
	MAX-ACCESS read-only
	STATUS current
	DESCRIPTION
		"Total number of zone notifies sent to the clients."
	::= { ltmDnsExpressStatEntry 8 }

ltmDnsExpressStatDnsxXfrMsgs OBJECT-TYPE
	SYNTAX Counter64
	MAX-ACCESS read-only
	STATUS current
	DESCRIPTION
		"Total number of zone transfer messages sent to the clients from DNS Express."
	::= { ltmDnsExpressStatEntry 9 }

ltmDnsExpressStatXfrNotifiesFailed OBJECT-TYPE
	SYNTAX Counter64
	MAX-ACCESS read-only
	STATUS current
	DESCRIPTION
		"Total number of failures when sending notifies to the clients."
	::= { ltmDnsExpressStatEntry 10 }

ltmDnsExpressStatTsigMissing OBJECT-TYPE
	SYNTAX Counter64
	MAX-ACCESS read-only
	STATUS current
	DESCRIPTION
		"Total number of zone transfer queries without TSIG while it is required."
	::= { ltmDnsExpressStatEntry 11 }

ltmDnsExpressStatTsigNotRequired OBJECT-TYPE
	SYNTAX Counter64
	MAX-ACCESS read-only
	STATUS current
	DESCRIPTION
		"Total number of zone transfer queries without TSIG and TSIG is not required."
	::= { ltmDnsExpressStatEntry 12 }

ltmDnsExpressStatTsigVerified OBJECT-TYPE
	SYNTAX Counter64
	MAX-ACCESS read-only
	STATUS current
	DESCRIPTION
		"Total number of zone transfer queries whose HMAC is verified."
	::= { ltmDnsExpressStatEntry 13 }

ltmDnsExpressStatTsigBadKey OBJECT-TYPE
	SYNTAX Counter64
	MAX-ACCESS read-only
	STATUS current
	DESCRIPTION
		"Total number of zone transfer queries with a bad key."
	::= { ltmDnsExpressStatEntry 14 }

ltmDnsExpressStatTsigBadSig OBJECT-TYPE
	SYNTAX Counter64
	MAX-ACCESS read-only
	STATUS current
	DESCRIPTION
		"Total number of zone transfer queries with a bad HMAC."
	::= { ltmDnsExpressStatEntry 15 }

ltmDnsExpressStatTsigBadTime OBJECT-TYPE
	SYNTAX Counter64
	MAX-ACCESS read-only
	STATUS current
	DESCRIPTION
		"Total number of zone transfer queries with a bad time."
	::= { ltmDnsExpressStatEntry 16 }

--==================================================================
-- Tmm_dns_server_stat
--==================================================================
ltmDnsServerStatResetStats OBJECT-TYPE
	SYNTAX INTEGER
	MAX-ACCESS read-write
	STATUS current
	DESCRIPTION
		"The action to reset resettable statistics data in ltmDnsServerStat.
		 Setting this value to 1 will reset statistics data.
		 Note, some statistics data may not be reset including data that are incremental counters."
	::= { ltmDnsServerStat 1 }

ltmDnsServerStatNumber OBJECT-TYPE
	SYNTAX INTEGER
	MAX-ACCESS read-only
	STATUS current
	DESCRIPTION
		"The number of ltmDnsServerStat entries in the table."
	::= { ltmDnsServerStat 2 }

ltmDnsServerStatTable OBJECT-TYPE
	SYNTAX SEQUENCE OF LtmDnsServerStatEntry
	MAX-ACCESS not-accessible
	STATUS current
	DESCRIPTION
		"A table containing statistics information about DNS server zone transfer."
	::= { ltmDnsServerStat 3 }

ltmDnsServerStatEntry OBJECT-TYPE
	SYNTAX  LtmDnsServerStatEntry
	MAX-ACCESS not-accessible
	STATUS current
	DESCRIPTION
		"Columns in the ltmDnsServerStat Table"
	INDEX {
		ltmDnsServerStatName
	}
	::= { ltmDnsServerStatTable 1 }

LtmDnsServerStatEntry ::=
	SEQUENCE {
        	ltmDnsServerStatName                                      LongDisplayString,
        	ltmDnsServerStatXfrQueries                                Counter64,
        	ltmDnsServerStatXfrResponses                              Counter64,
        	ltmDnsServerStatXfrNotifies                               Counter64,
        	ltmDnsServerStatXfrNotifyFailed                           Counter64
	}

ltmDnsServerStatName OBJECT-TYPE
	SYNTAX LongDisplayString
	MAX-ACCESS read-only
	STATUS current
	DESCRIPTION
		"The name of DNS server."
	::= { ltmDnsServerStatEntry 1 }

ltmDnsServerStatXfrQueries OBJECT-TYPE
	SYNTAX Counter64
	MAX-ACCESS read-only
	STATUS current
	DESCRIPTION
		"Total number of zone transfer queries."
	::= { ltmDnsServerStatEntry 2 }

ltmDnsServerStatXfrResponses OBJECT-TYPE
	SYNTAX Counter64
	MAX-ACCESS read-only
	STATUS current
	DESCRIPTION
		"Total number of zone transfer responses."
	::= { ltmDnsServerStatEntry 3 }

ltmDnsServerStatXfrNotifies OBJECT-TYPE
	SYNTAX Counter64
	MAX-ACCESS read-only
	STATUS current
	DESCRIPTION
		"Total number of zone transfer notifies."
	::= { ltmDnsServerStatEntry 4 }

ltmDnsServerStatXfrNotifyFailed OBJECT-TYPE
	SYNTAX Counter64
	MAX-ACCESS read-only
	STATUS current
	DESCRIPTION
		"Total number of zone transfer notify failures."
	::= { ltmDnsServerStatEntry 5 }

--==================================================================
-- Dns_cache_forward_zone
--==================================================================
ltmDnsCacheForwardZoneNumber OBJECT-TYPE
	SYNTAX INTEGER
	MAX-ACCESS read-only
	STATUS current
	DESCRIPTION
		"The number of ltmDnsCacheForwardZone entries in the table."
	::= { ltmDnsCacheForwardZone 1 }

ltmDnsCacheForwardZoneTable OBJECT-TYPE
	SYNTAX SEQUENCE OF LtmDnsCacheForwardZoneEntry
	MAX-ACCESS not-accessible
	STATUS current
	DESCRIPTION
		"A table containing information about DNS Cache Forward Zone."
	::= { ltmDnsCacheForwardZone 2 }

ltmDnsCacheForwardZoneEntry OBJECT-TYPE
	SYNTAX  LtmDnsCacheForwardZoneEntry
	MAX-ACCESS not-accessible
	STATUS current
	DESCRIPTION
		"Columns in the ltmDnsCacheForwardZone Table"
	INDEX {
		ltmDnsCacheForwardZoneName,
		ltmDnsCacheForwardZoneCacheName
	}
	::= { ltmDnsCacheForwardZoneTable 1 }

LtmDnsCacheForwardZoneEntry ::=
	SEQUENCE {
        	ltmDnsCacheForwardZoneName                                LongDisplayString,
        	ltmDnsCacheForwardZoneCacheName                           LongDisplayString
	}

ltmDnsCacheForwardZoneName OBJECT-TYPE
	SYNTAX LongDisplayString
	MAX-ACCESS read-only
	STATUS current
	DESCRIPTION
		"The name of DNS Cache Forward Zone."
	::= { ltmDnsCacheForwardZoneEntry 1 }

ltmDnsCacheForwardZoneCacheName OBJECT-TYPE
	SYNTAX LongDisplayString
	MAX-ACCESS read-only
	STATUS current
	DESCRIPTION
		"The name of DNS Cache to which the specified Forward Zone belongs."
	::= { ltmDnsCacheForwardZoneEntry 2 }

--==================================================================
-- Dns_cache_forward_zone_name_server
--==================================================================
ltmDnsCacheForwardZoneNameServerNumber OBJECT-TYPE
	SYNTAX INTEGER
	MAX-ACCESS read-only
	STATUS current
	DESCRIPTION
		"The number of ltmDnsCacheForwardZoneNameServer entries in the table."
	::= { ltmDnsCacheForwardZoneNameServer 1 }

ltmDnsCacheForwardZoneNameServerTable OBJECT-TYPE
	SYNTAX SEQUENCE OF LtmDnsCacheForwardZoneNameServerEntry
	MAX-ACCESS not-accessible
	STATUS current
	DESCRIPTION
		"A table containing information about DNS Cache Forward Zone Nameserver."
	::= { ltmDnsCacheForwardZoneNameServer 2 }

ltmDnsCacheForwardZoneNameServerEntry OBJECT-TYPE
	SYNTAX  LtmDnsCacheForwardZoneNameServerEntry
	MAX-ACCESS not-accessible
	STATUS current
	DESCRIPTION
		"Columns in the ltmDnsCacheForwardZoneNameServer Table"
	INDEX {
		ltmDnsCacheForwardZoneNameServerAddrType,
		ltmDnsCacheForwardZoneNameServerAddr,
		ltmDnsCacheForwardZoneNameServerPort,
		ltmDnsCacheForwardZoneNameServerForwardZoneName,
		ltmDnsCacheForwardZoneNameServerCacheName
	}
	::= { ltmDnsCacheForwardZoneNameServerTable 1 }

LtmDnsCacheForwardZoneNameServerEntry ::=
	SEQUENCE {
        	ltmDnsCacheForwardZoneNameServerAddrType                  InetAddressType,
        	ltmDnsCacheForwardZoneNameServerAddr                      InetAddress,
        	ltmDnsCacheForwardZoneNameServerPort                      InetPortNumber,
        	ltmDnsCacheForwardZoneNameServerForwardZoneName           LongDisplayString,
        	ltmDnsCacheForwardZoneNameServerCacheName                 LongDisplayString
	}

ltmDnsCacheForwardZoneNameServerAddrType OBJECT-TYPE
	SYNTAX InetAddressType
	MAX-ACCESS read-only
	STATUS current
	DESCRIPTION
		"The IP address type of the ltmDnsCacheForwardZoneNameServerIp."
	::= { ltmDnsCacheForwardZoneNameServerEntry 1 }

ltmDnsCacheForwardZoneNameServerAddr OBJECT-TYPE
	SYNTAX InetAddress
	MAX-ACCESS read-only
	STATUS current
	DESCRIPTION
		"The IP address of the specified nameserver. It is interpreted within
	         the context of a ltmDnsCacheForwardZoneNameServerIpType"
	::= { ltmDnsCacheForwardZoneNameServerEntry 2 }

ltmDnsCacheForwardZoneNameServerPort OBJECT-TYPE
	SYNTAX InetPortNumber
	MAX-ACCESS read-only
	STATUS current
	DESCRIPTION
		"The port of the specified nameserver."
	::= { ltmDnsCacheForwardZoneNameServerEntry 3 }

ltmDnsCacheForwardZoneNameServerForwardZoneName OBJECT-TYPE
	SYNTAX LongDisplayString
	MAX-ACCESS read-only
	STATUS current
	DESCRIPTION
		"The name of DNS Cache Forward Zone to which the specified nameserver belongs."
	::= { ltmDnsCacheForwardZoneNameServerEntry 4 }

ltmDnsCacheForwardZoneNameServerCacheName OBJECT-TYPE
	SYNTAX LongDisplayString
	MAX-ACCESS read-only
	STATUS current
	DESCRIPTION
		"The name of DNS Cache to which the specified nameserver, and it's parent Forward Zone, belongs."
	::= { ltmDnsCacheForwardZoneNameServerEntry 5 }

--==================================================================
-- Clientssl_certkeychain
--==================================================================
ltmClientSslCertKeyChainNumber OBJECT-TYPE
	SYNTAX INTEGER
	MAX-ACCESS read-only
	STATUS current
	DESCRIPTION
		"The number of ltmClientSslCertKeyChain entries in the table."
	::= { ltmClientSslCertKeyChain 1 }

ltmClientSslCertKeyChainTable OBJECT-TYPE
	SYNTAX SEQUENCE OF LtmClientSslCertKeyChainEntry
	MAX-ACCESS not-accessible
	STATUS current
	DESCRIPTION
		"A table containing cert, key and chain configuration of client-side SSL profiles."
	::= { ltmClientSslCertKeyChain 2 }

ltmClientSslCertKeyChainEntry OBJECT-TYPE
	SYNTAX  LtmClientSslCertKeyChainEntry
	MAX-ACCESS not-accessible
	STATUS current
	DESCRIPTION
		"Columns in the ltmClientSslCertKeyChain Table"
	INDEX {
		ltmClientSslCertKeyChainName,
		ltmClientSslCertKeyChainClientssl
	}
	::= { ltmClientSslCertKeyChainTable 1 }

LtmClientSslCertKeyChainEntry ::=
	SEQUENCE {
        	ltmClientSslCertKeyChainName                              LongDisplayString,
        	ltmClientSslCertKeyChainClientssl                         LongDisplayString,
        	ltmClientSslCertKeyChainCert                              LongDisplayString,
        	ltmClientSslCertKeyChainKey                               LongDisplayString,
        	ltmClientSslCertKeyChainChain                             LongDisplayString,
        	ltmClientSslCertKeyChainOcspStplParams                    LongDisplayString
	}

ltmClientSslCertKeyChainName OBJECT-TYPE
	SYNTAX LongDisplayString
	MAX-ACCESS read-only
	STATUS current
	DESCRIPTION
		"The name of a certkeychain set."
	::= { ltmClientSslCertKeyChainEntry 1 }

ltmClientSslCertKeyChainClientssl OBJECT-TYPE
	SYNTAX LongDisplayString
	MAX-ACCESS read-only
	STATUS current
	DESCRIPTION
		"The name of a ClientSSL profile the set is related to."
	::= { ltmClientSslCertKeyChainEntry 2 }

ltmClientSslCertKeyChainCert OBJECT-TYPE
	SYNTAX LongDisplayString
	MAX-ACCESS read-only
	STATUS current
	DESCRIPTION
		"The certificate file name."
	::= { ltmClientSslCertKeyChainEntry 3 }

ltmClientSslCertKeyChainKey OBJECT-TYPE
	SYNTAX LongDisplayString
	MAX-ACCESS read-only
	STATUS current
	DESCRIPTION
		"The key file name."
	::= { ltmClientSslCertKeyChainEntry 4 }

ltmClientSslCertKeyChainChain OBJECT-TYPE
	SYNTAX LongDisplayString
	MAX-ACCESS read-only
	STATUS current
	DESCRIPTION
		"The certificate chain file name."
	::= { ltmClientSslCertKeyChainEntry 5 }

ltmClientSslCertKeyChainOcspStplParams OBJECT-TYPE
	SYNTAX LongDisplayString
	MAX-ACCESS read-only
	STATUS current
	DESCRIPTION
		"The name of the OCSP Stapling Parameters object."
	::= { ltmClientSslCertKeyChainEntry 6 }

--==================================================================
-- Dos_attack_data_stat
--==================================================================
ltmDosAttackDataStatResetStats OBJECT-TYPE
	SYNTAX INTEGER
	MAX-ACCESS read-write
	STATUS current
	DESCRIPTION
		"The action to reset resettable statistics data in ltmDosAttackDataStat.
		 Setting this value to 1 will reset statistics data.
		 Note, some statistics data may not be reset including data that are incremental counters."
	::= { ltmDosAttackDataStat 1 }

ltmDosAttackDataStatNumber OBJECT-TYPE
	SYNTAX INTEGER
	MAX-ACCESS read-only
	STATUS current
	DESCRIPTION
		"The number of ltmDosAttackDataStat entries in the table."
	::= { ltmDosAttackDataStat 2 }

ltmDosAttackDataStatTable OBJECT-TYPE
	SYNTAX SEQUENCE OF LtmDosAttackDataStatEntry
	MAX-ACCESS not-accessible
	STATUS current
	DESCRIPTION
		"A table containing statistic information of DoS attack data."
	::= { ltmDosAttackDataStat 3 }

ltmDosAttackDataStatEntry OBJECT-TYPE
	SYNTAX  LtmDosAttackDataStatEntry
	MAX-ACCESS not-accessible
	STATUS current
	DESCRIPTION
		"Columns in the ltmDosAttackDataStat Table"
	INDEX {
		ltmDosAttackDataStatDeviceName,
		ltmDosAttackDataStatVectorName,
		ltmDosAttackDataStatAttackType
	}
	::= { ltmDosAttackDataStatTable 1 }

LtmDosAttackDataStatEntry ::=
	SEQUENCE {
        	ltmDosAttackDataStatDeviceName                            LongDisplayString,
        	ltmDosAttackDataStatVectorName                            LongDisplayString,
        	ltmDosAttackDataStatAttackType                            INTEGER,
        	ltmDosAttackDataStatAttackDetected                        Counter64,
        	ltmDosAttackDataStatAttackCount                           Counter64,
        	ltmDosAttackDataStatStats                                 Counter64,
        	ltmDosAttackDataStatStatsRate                             Counter64,
        	ltmDosAttackDataStatStats1m                               Counter64,
        	ltmDosAttackDataStatStats1h                               Counter64,
        	ltmDosAttackDataStatDrops                                 Counter64,
        	ltmDosAttackDataStatDropsRate                             Counter64,
        	ltmDosAttackDataStatDrops1m                               Counter64,
        	ltmDosAttackDataStatDrops1h                               Counter64,
        	ltmDosAttackDataStatWlCount                               Counter64
	}

ltmDosAttackDataStatDeviceName OBJECT-TYPE
	SYNTAX LongDisplayString
	MAX-ACCESS read-only
	STATUS current
	DESCRIPTION
		"The name of the DoS Device."
	::= { ltmDosAttackDataStatEntry 1 }

ltmDosAttackDataStatVectorName OBJECT-TYPE
	SYNTAX LongDisplayString
	MAX-ACCESS read-only
	STATUS current
	DESCRIPTION
		"The name of the DoS Vector."
	::= { ltmDosAttackDataStatEntry 2 }

ltmDosAttackDataStatAttackType OBJECT-TYPE
	SYNTAX INTEGER {
		etherBrdcstPkt(1),
		etherMulticstPkt(2),
		etherMacSaEqDa(3),
		arpFlood(4),
		badVer(5),
		hdrLenTooShort(6),
		hdrLenGtL2Len(7),
		ipLenGtL2Len(8),
		l2LenGgtIpLen(9),
		noL4(10),
		badTtlVal(11),
		ttlLeqOne(12),
		ipErrChksum(13),
		ipOptFrames(14),
		ipFragFlood(15),
		badIgmpFrame(16),
		ipShortFrag(17),
		igmpFlood(18),
		badIpv6Ver(19),
		ipv6LenGtL2Len(20),
		payloadLenLsL2Len(21),
		tooManyExtHdrs(22),
		dupExtHdr(23),
		extHdrTooLarge(24),
		l4ExtHdrsGoEnd(25),
		badIpv6HopCnt(26),
		hopCntLeqOne(27),
		routingHeaderType0(28),
		ipv6ExtHdrFrames(29),
		ipv6FragFlood(30),
		badExtHdrOrder(31),
		ipv6ShortFrag(32),
		igmpFragFlood(33),
		tcpHdrLenTooShort(34),
		tclHdrLenGtL2Len(35),
		unkTcpOptType(36),
		optPresentWithIllegalLen(37),
		tcpOptOverrunsTcpHdr(38),
		badTcpChksum(39),
		badTcpFlagsAllSet(40),
		badTcpFlagsAllClr(41),
		synAndFinSet(42),
		finOnlySet(43),
		tcpSynFlood(44),
		tcpSynackFlood(45),
		tcpRstFlood(46),
		badIcmpChksum(47),
		tcpBadUrg(48),
		tcpWindowSize(49),
		ipv6AtomicFrag(50),
		badUdpHdr(51),
		badUdpChksum(52),
		ipBadSrc(53),
		ipv6BadSrc(54),
		badIcmpFrame(55),
		icmpv4Flood(56),
		icmpFrag(57),
		icmpFrameTooLarge(58),
		icmpv6Flood(59),
		hostUnreachable(60),
		tidcmp(61),
		udpFlood(62),
		dnsOversize(63),
		landAttack(64),
		dnsResponseFlood(65),
		dnsMalformed(66),
		dnsQdcountLimit(67),
		dnsAnyQuery(68),
		dnsAQuery(69),
		dnsPtrQuery(70),
		dnsNsQuery(71),
		dnsSoaQuery(72),
		dnsCnameQuery(73),
		dnsMxQuery(74),
		dnsAaaaQuery(75),
		dnsTxtQuery(76),
		dnsSrvQuery(77),
		dnsAxfrQuery(78),
		dnsIxfrQuery(79),
		dnsOtherQuery(80),
		ipOtherFrag(81),
		ipv6OtherFrag(82),
		sipMalformed(83),
		sipInviteMethod(84),
		sipAckMethod(85),
		sipOptionsMethod(86),
		sipByeMethod(87),
		sipCancelMethod(88),
		sipRegisterMethod(89),
		sipPublishMethod(90),
		sipNotifyMethod(91),
		sipSubscribeMethod(92),
		sipMessageMethod(93),
		sipPrackMethod(94),
		sipOtherMethod(95),
		ipOverlapFrag(96),
		ipv6OverlapFrag(97),
		badIpOpt(98),
		tcpAckFlood(99),
		sweep(101),
		flood(102),
		unkIpoptType(103),
		badSctpChksum(104),
		ipUnkProt(105),
		tcpSynOversize(106)
	}
	MAX-ACCESS read-only
	STATUS current
	DESCRIPTION
		"The DoS attack vector type."
	::= { ltmDosAttackDataStatEntry 3 }

ltmDosAttackDataStatAttackDetected OBJECT-TYPE
	SYNTAX Counter64
	MAX-ACCESS read-only
	STATUS current
	DESCRIPTION
		"A Boolean representing whether or not an attack is currently
	        occurring."
	::= { ltmDosAttackDataStatEntry 4 }

ltmDosAttackDataStatAttackCount OBJECT-TYPE
	SYNTAX Counter64
	MAX-ACCESS read-only
	STATUS current
	DESCRIPTION
		"The number of attacks detected."
	::= { ltmDosAttackDataStatEntry 5 }

ltmDosAttackDataStatStats OBJECT-TYPE
	SYNTAX Counter64
	MAX-ACCESS read-only
	STATUS current
	DESCRIPTION
		"The number of attack packets received."
	::= { ltmDosAttackDataStatEntry 6 }

ltmDosAttackDataStatStatsRate OBJECT-TYPE
	SYNTAX Counter64
	MAX-ACCESS read-only
	STATUS current
	DESCRIPTION
		"The number of attack packets received per second."
	::= { ltmDosAttackDataStatEntry 7 }

ltmDosAttackDataStatStats1m OBJECT-TYPE
	SYNTAX Counter64
	MAX-ACCESS read-only
	STATUS current
	DESCRIPTION
		"The number of attack packets received in the last minute."
	::= { ltmDosAttackDataStatEntry 8 }

ltmDosAttackDataStatStats1h OBJECT-TYPE
	SYNTAX Counter64
	MAX-ACCESS read-only
	STATUS current
	DESCRIPTION
		"The number of attack packets received in the last hour."
	::= { ltmDosAttackDataStatEntry 9 }

ltmDosAttackDataStatDrops OBJECT-TYPE
	SYNTAX Counter64
	MAX-ACCESS read-only
	STATUS current
	DESCRIPTION
		"The number of attack packets dropped."
	::= { ltmDosAttackDataStatEntry 10 }

ltmDosAttackDataStatDropsRate OBJECT-TYPE
	SYNTAX Counter64
	MAX-ACCESS read-only
	STATUS current
	DESCRIPTION
		"The number of attack packets dropped per second."
	::= { ltmDosAttackDataStatEntry 11 }

ltmDosAttackDataStatDrops1m OBJECT-TYPE
	SYNTAX Counter64
	MAX-ACCESS read-only
	STATUS current
	DESCRIPTION
		"The number of attack packets dropped in the last minute."
	::= { ltmDosAttackDataStatEntry 12 }

ltmDosAttackDataStatDrops1h OBJECT-TYPE
	SYNTAX Counter64
	MAX-ACCESS read-only
	STATUS current
	DESCRIPTION
		"The number of attack packets dropped in the last hour."
	::= { ltmDosAttackDataStatEntry 13 }

ltmDosAttackDataStatWlCount OBJECT-TYPE
	SYNTAX Counter64
	MAX-ACCESS read-only
	STATUS current
	DESCRIPTION
		"Total number of whitelist hits."
	::= { ltmDosAttackDataStatEntry 14 }

--==================================================================
-- Network_attack_data_stat
--==================================================================
ltmNetworkAttackDataStatResetStats OBJECT-TYPE
	SYNTAX INTEGER
	MAX-ACCESS read-write
	STATUS current
	DESCRIPTION
		"The action to reset resettable statistics data in ltmNetworkAttackDataStat.
		 Setting this value to 1 will reset statistics data.
		 Note, some statistics data may not be reset including data that are incremental counters."
	::= { ltmNetworkAttackDataStat 1 }

ltmNetworkAttackDataStatNumber OBJECT-TYPE
	SYNTAX INTEGER
	MAX-ACCESS read-only
	STATUS current
	DESCRIPTION
		"The number of ltmNetworkAttackDataStat entries in the table."
	::= { ltmNetworkAttackDataStat 2 }

ltmNetworkAttackDataStatTable OBJECT-TYPE
	SYNTAX SEQUENCE OF LtmNetworkAttackDataStatEntry
	MAX-ACCESS not-accessible
	STATUS current
	DESCRIPTION
		"A table containing statistic information of Network DoS attack data."
	::= { ltmNetworkAttackDataStat 3 }

ltmNetworkAttackDataStatEntry OBJECT-TYPE
	SYNTAX  LtmNetworkAttackDataStatEntry
	MAX-ACCESS not-accessible
	STATUS current
	DESCRIPTION
		"Columns in the ltmNetworkAttackDataStat Table"
	INDEX {
		ltmNetworkAttackDataStatProfileName,
		ltmNetworkAttackDataStatVectorName,
		ltmNetworkAttackDataStatAttackType,
		ltmNetworkAttackDataStatVsName
	}
	::= { ltmNetworkAttackDataStatTable 1 }

LtmNetworkAttackDataStatEntry ::=
	SEQUENCE {
        	ltmNetworkAttackDataStatProfileName                       LongDisplayString,
        	ltmNetworkAttackDataStatVsName                            LongDisplayString,
        	ltmNetworkAttackDataStatVectorName                        LongDisplayString,
        	ltmNetworkAttackDataStatAttackType                        INTEGER,
        	ltmNetworkAttackDataStatAttackDetected                    Counter64,
        	ltmNetworkAttackDataStatAttackCount                       Counter64,
        	ltmNetworkAttackDataStatStats                             Counter64,
        	ltmNetworkAttackDataStatStatsRate                         Counter64,
        	ltmNetworkAttackDataStatStats1m                           Counter64,
        	ltmNetworkAttackDataStatStats1h                           Counter64,
        	ltmNetworkAttackDataStatDrops                             Counter64,
        	ltmNetworkAttackDataStatDropsRate                         Counter64,
        	ltmNetworkAttackDataStatDrops1m                           Counter64,
        	ltmNetworkAttackDataStatDrops1h                           Counter64,
        	ltmNetworkAttackDataStatWlCount                           Counter64
	}

ltmNetworkAttackDataStatProfileName OBJECT-TYPE
	SYNTAX LongDisplayString
	MAX-ACCESS read-only
	STATUS current
	DESCRIPTION
		"The name of the DoS Profile."
	::= { ltmNetworkAttackDataStatEntry 1 }

ltmNetworkAttackDataStatVsName OBJECT-TYPE
	SYNTAX LongDisplayString
	MAX-ACCESS read-only
	STATUS current
	DESCRIPTION
		"The name of the virtual server."
	::= { ltmNetworkAttackDataStatEntry 2 }

ltmNetworkAttackDataStatVectorName OBJECT-TYPE
	SYNTAX LongDisplayString
	MAX-ACCESS read-only
	STATUS current
	DESCRIPTION
		"The name of the DoS Vector."
	::= { ltmNetworkAttackDataStatEntry 3 }

ltmNetworkAttackDataStatAttackType OBJECT-TYPE
	SYNTAX INTEGER {
		ipOptFrames(1),
		ipLowTtl(2),
		hopCntLow(3),
		icmpFrag(4),
		ipFragFlood(5),
		tooManyExtHdrs(6),
		extHdrTooLarge(7),
		ipv6ExtHdrFrames(8),
		ipv6FragFlood(9),
		unkTcpOptType(10),
		optPresentWithIllegalLen(11),
		tcpOptOverrunsTcpHdr(12),
		tcpSynFlood(13),
		tcpSynackFlood(14),
		tcpRstFlood(15),
		tcpBadUrg(16),
		tcpWindowSize(17),
		hostUnreachable(18),
		tidcmp(19),
		icmpv4Flood(20),
		icmpv6Flood(21),
		udpFlood(22),
		sweep(23),
		tcpSynOversize(24)
	}
	MAX-ACCESS read-only
	STATUS current
	DESCRIPTION
		"The DoS attack vector type."
	::= { ltmNetworkAttackDataStatEntry 4 }

ltmNetworkAttackDataStatAttackDetected OBJECT-TYPE
	SYNTAX Counter64
	MAX-ACCESS read-only
	STATUS current
	DESCRIPTION
		"A Boolean representing whether or not an attack is currently
	        occurring."
	::= { ltmNetworkAttackDataStatEntry 5 }

ltmNetworkAttackDataStatAttackCount OBJECT-TYPE
	SYNTAX Counter64
	MAX-ACCESS read-only
	STATUS current
	DESCRIPTION
		"The number of attacks detected."
	::= { ltmNetworkAttackDataStatEntry 6 }

ltmNetworkAttackDataStatStats OBJECT-TYPE
	SYNTAX Counter64
	MAX-ACCESS read-only
	STATUS current
	DESCRIPTION
		"The number of attack packets received."
	::= { ltmNetworkAttackDataStatEntry 7 }

ltmNetworkAttackDataStatStatsRate OBJECT-TYPE
	SYNTAX Counter64
	MAX-ACCESS read-only
	STATUS current
	DESCRIPTION
		"The number of attack packets received per second."
	::= { ltmNetworkAttackDataStatEntry 8 }

ltmNetworkAttackDataStatStats1m OBJECT-TYPE
	SYNTAX Counter64
	MAX-ACCESS read-only
	STATUS current
	DESCRIPTION
		"The number of attack packets received in the last minute."
	::= { ltmNetworkAttackDataStatEntry 9 }

ltmNetworkAttackDataStatStats1h OBJECT-TYPE
	SYNTAX Counter64
	MAX-ACCESS read-only
	STATUS current
	DESCRIPTION
		"The number of attack packets received in the last hour."
	::= { ltmNetworkAttackDataStatEntry 10 }

ltmNetworkAttackDataStatDrops OBJECT-TYPE
	SYNTAX Counter64
	MAX-ACCESS read-only
	STATUS current
	DESCRIPTION
		"The number of attack packets dropped."
	::= { ltmNetworkAttackDataStatEntry 11 }

ltmNetworkAttackDataStatDropsRate OBJECT-TYPE
	SYNTAX Counter64
	MAX-ACCESS read-only
	STATUS current
	DESCRIPTION
		"The number of attack packets dropped per second."
	::= { ltmNetworkAttackDataStatEntry 12 }

ltmNetworkAttackDataStatDrops1m OBJECT-TYPE
	SYNTAX Counter64
	MAX-ACCESS read-only
	STATUS current
	DESCRIPTION
		"The number of attack packets dropped in the last minute."
	::= { ltmNetworkAttackDataStatEntry 13 }

ltmNetworkAttackDataStatDrops1h OBJECT-TYPE
	SYNTAX Counter64
	MAX-ACCESS read-only
	STATUS current
	DESCRIPTION
		"The number of attack packets dropped in the last hour."
	::= { ltmNetworkAttackDataStatEntry 14 }

ltmNetworkAttackDataStatWlCount OBJECT-TYPE
	SYNTAX Counter64
	MAX-ACCESS read-only
	STATUS current
	DESCRIPTION
		"Total number of whitelist hits."
	::= { ltmNetworkAttackDataStatEntry 15 }

--==================================================================
-- Fw_admin_ip_rule_stat
--==================================================================
ltmFwAdminIpRuleStatNumber OBJECT-TYPE
	SYNTAX INTEGER
	MAX-ACCESS read-only
	STATUS current
	DESCRIPTION
		"The number of ltmFwAdminIpRuleStat entries in the table."
	::= { ltmFwAdminIpRuleStat 1 }

ltmFwAdminIpRuleStatTable OBJECT-TYPE
	SYNTAX SEQUENCE OF LtmFwAdminIpRuleStatEntry
	MAX-ACCESS not-accessible
	STATUS current
	DESCRIPTION
		"A table containing statistic information of Management IP Firewall Rules."
	::= { ltmFwAdminIpRuleStat 2 }

ltmFwAdminIpRuleStatEntry OBJECT-TYPE
	SYNTAX  LtmFwAdminIpRuleStatEntry
	MAX-ACCESS not-accessible
	STATUS current
	DESCRIPTION
		"Columns in the ltmFwAdminIpRuleStat Table"
	INDEX {
		ltmFwAdminIpRuleStatRuleName,
		ltmFwAdminIpRuleStatContainerName
	}
	::= { ltmFwAdminIpRuleStatTable 1 }

LtmFwAdminIpRuleStatEntry ::=
	SEQUENCE {
        	ltmFwAdminIpRuleStatRuleName                              LongDisplayString,
        	ltmFwAdminIpRuleStatContainerName                         LongDisplayString,
        	ltmFwAdminIpRuleStatCounter                               Counter64
	}

ltmFwAdminIpRuleStatRuleName OBJECT-TYPE
	SYNTAX LongDisplayString
	MAX-ACCESS read-only
	STATUS current
	DESCRIPTION
		"The name of the rule."
	::= { ltmFwAdminIpRuleStatEntry 1 }

ltmFwAdminIpRuleStatContainerName OBJECT-TYPE
	SYNTAX LongDisplayString
	MAX-ACCESS read-only
	STATUS current
	DESCRIPTION
		"The name of the containing item."
	::= { ltmFwAdminIpRuleStatEntry 2 }

ltmFwAdminIpRuleStatCounter OBJECT-TYPE
	SYNTAX Counter64
	MAX-ACCESS read-only
	STATUS current
	DESCRIPTION
		"The number of packets matching this rule."
	::= { ltmFwAdminIpRuleStatEntry 3 }

--==================================================================
-- Fw_ipint_global_stat
--==================================================================
ltmFwIpintGlobalStatResetStats OBJECT-TYPE
	SYNTAX INTEGER
	MAX-ACCESS read-write
	STATUS current
	DESCRIPTION
		"The action to reset resettable statistics data in ltmFwIpintGlobalStat.
		 Setting this value to 1 will reset statistics data.
		 Note, some statistics data may not be reset including data that are incremental counters."
	::= { ltmFwIpintGlobalStat 1 }

ltmFwIpintGlobalStatNumber OBJECT-TYPE
	SYNTAX INTEGER
	MAX-ACCESS read-only
	STATUS current
	DESCRIPTION
		"The number of ltmFwIpintGlobalStat entries in the table."
	::= { ltmFwIpintGlobalStat 2 }

ltmFwIpintGlobalStatTable OBJECT-TYPE
	SYNTAX SEQUENCE OF LtmFwIpintGlobalStatEntry
	MAX-ACCESS not-accessible
	STATUS current
	DESCRIPTION
		"A table containing statistic information of global IP Intelligence data."
	::= { ltmFwIpintGlobalStat 3 }

ltmFwIpintGlobalStatEntry OBJECT-TYPE
	SYNTAX  LtmFwIpintGlobalStatEntry
	MAX-ACCESS not-accessible
	STATUS current
	DESCRIPTION
		"Columns in the ltmFwIpintGlobalStat Table"
	INDEX {
		ltmFwIpintGlobalStatBlClassName
	}
	::= { ltmFwIpintGlobalStatTable 1 }

LtmFwIpintGlobalStatEntry ::=
	SEQUENCE {
        	ltmFwIpintGlobalStatBlClassName                           LongDisplayString,
        	ltmFwIpintGlobalStatSrcIpBlacklist                        Counter64,
        	ltmFwIpintGlobalStatDstIpBlacklist                        Counter64
	}

ltmFwIpintGlobalStatBlClassName OBJECT-TYPE
	SYNTAX LongDisplayString
	MAX-ACCESS read-only
	STATUS current
	DESCRIPTION
		"The blacklist class name."
	::= { ltmFwIpintGlobalStatEntry 1 }

ltmFwIpintGlobalStatSrcIpBlacklist OBJECT-TYPE
	SYNTAX Counter64
	MAX-ACCESS read-only
	STATUS current
	DESCRIPTION
		"The number of packets whose source IP matched this category."
	::= { ltmFwIpintGlobalStatEntry 2 }

ltmFwIpintGlobalStatDstIpBlacklist OBJECT-TYPE
	SYNTAX Counter64
	MAX-ACCESS read-only
	STATUS current
	DESCRIPTION
		"The number of packets whose destination IP matched this category."
	::= { ltmFwIpintGlobalStatEntry 3 }

--==================================================================
-- Fw_ipint_virtual_stat
--==================================================================
ltmFwIpintVirtualStatResetStats OBJECT-TYPE
	SYNTAX INTEGER
	MAX-ACCESS read-write
	STATUS current
	DESCRIPTION
		"The action to reset resettable statistics data in ltmFwIpintVirtualStat.
		 Setting this value to 1 will reset statistics data.
		 Note, some statistics data may not be reset including data that are incremental counters."
	::= { ltmFwIpintVirtualStat 1 }

ltmFwIpintVirtualStatNumber OBJECT-TYPE
	SYNTAX INTEGER
	MAX-ACCESS read-only
	STATUS current
	DESCRIPTION
		"The number of ltmFwIpintVirtualStat entries in the table."
	::= { ltmFwIpintVirtualStat 2 }

ltmFwIpintVirtualStatTable OBJECT-TYPE
	SYNTAX SEQUENCE OF LtmFwIpintVirtualStatEntry
	MAX-ACCESS not-accessible
	STATUS current
	DESCRIPTION
		"A table containing statistic information of virtual server IP Intelligence data."
	::= { ltmFwIpintVirtualStat 3 }

ltmFwIpintVirtualStatEntry OBJECT-TYPE
	SYNTAX  LtmFwIpintVirtualStatEntry
	MAX-ACCESS not-accessible
	STATUS current
	DESCRIPTION
		"Columns in the ltmFwIpintVirtualStat Table"
	INDEX {
		ltmFwIpintVirtualStatContextName,
		ltmFwIpintVirtualStatBlClassName
	}
	::= { ltmFwIpintVirtualStatTable 1 }

LtmFwIpintVirtualStatEntry ::=
	SEQUENCE {
        	ltmFwIpintVirtualStatContextName                          LongDisplayString,
        	ltmFwIpintVirtualStatBlClassName                          LongDisplayString,
        	ltmFwIpintVirtualStatSrcIpBlacklist                       Counter64,
        	ltmFwIpintVirtualStatDstIpBlacklist                       Counter64
	}

ltmFwIpintVirtualStatContextName OBJECT-TYPE
	SYNTAX LongDisplayString
	MAX-ACCESS read-only
	STATUS current
	DESCRIPTION
		"The name of the virtual server."
	::= { ltmFwIpintVirtualStatEntry 1 }

ltmFwIpintVirtualStatBlClassName OBJECT-TYPE
	SYNTAX LongDisplayString
	MAX-ACCESS read-only
	STATUS current
	DESCRIPTION
		"The blacklist class name."
	::= { ltmFwIpintVirtualStatEntry 2 }

ltmFwIpintVirtualStatSrcIpBlacklist OBJECT-TYPE
	SYNTAX Counter64
	MAX-ACCESS read-only
	STATUS current
	DESCRIPTION
		"The number of packets whose source IP matched this category."
	::= { ltmFwIpintVirtualStatEntry 3 }

ltmFwIpintVirtualStatDstIpBlacklist OBJECT-TYPE
	SYNTAX Counter64
	MAX-ACCESS read-only
	STATUS current
	DESCRIPTION
		"The number of packets whose destination IP matched this category."
	::= { ltmFwIpintVirtualStatEntry 4 }

--==================================================================
-- Fw_ipint_route_domain_stat
--==================================================================
ltmFwIpintRouteDomainStatResetStats OBJECT-TYPE
	SYNTAX INTEGER
	MAX-ACCESS read-write
	STATUS current
	DESCRIPTION
		"The action to reset resettable statistics data in ltmFwIpintRouteDomainStat.
		 Setting this value to 1 will reset statistics data.
		 Note, some statistics data may not be reset including data that are incremental counters."
	::= { ltmFwIpintRouteDomainStat 1 }

ltmFwIpintRouteDomainStatNumber OBJECT-TYPE
	SYNTAX INTEGER
	MAX-ACCESS read-only
	STATUS current
	DESCRIPTION
		"The number of ltmFwIpintRouteDomainStat entries in the table."
	::= { ltmFwIpintRouteDomainStat 2 }

ltmFwIpintRouteDomainStatTable OBJECT-TYPE
	SYNTAX SEQUENCE OF LtmFwIpintRouteDomainStatEntry
	MAX-ACCESS not-accessible
	STATUS current
	DESCRIPTION
		"A table containing statistic information of route domain IP Intelligence data."
	::= { ltmFwIpintRouteDomainStat 3 }

ltmFwIpintRouteDomainStatEntry OBJECT-TYPE
	SYNTAX  LtmFwIpintRouteDomainStatEntry
	MAX-ACCESS not-accessible
	STATUS current
	DESCRIPTION
		"Columns in the ltmFwIpintRouteDomainStat Table"
	INDEX {
		ltmFwIpintRouteDomainStatContextName,
		ltmFwIpintRouteDomainStatBlClassName
	}
	::= { ltmFwIpintRouteDomainStatTable 1 }

LtmFwIpintRouteDomainStatEntry ::=
	SEQUENCE {
        	ltmFwIpintRouteDomainStatContextName                      LongDisplayString,
        	ltmFwIpintRouteDomainStatBlClassName                      LongDisplayString,
        	ltmFwIpintRouteDomainStatSrcIpBlacklist                   Counter64,
        	ltmFwIpintRouteDomainStatDstIpBlacklist                   Counter64
	}

ltmFwIpintRouteDomainStatContextName OBJECT-TYPE
	SYNTAX LongDisplayString
	MAX-ACCESS read-only
	STATUS current
	DESCRIPTION
		"The name of the route domain."
	::= { ltmFwIpintRouteDomainStatEntry 1 }

ltmFwIpintRouteDomainStatBlClassName OBJECT-TYPE
	SYNTAX LongDisplayString
	MAX-ACCESS read-only
	STATUS current
	DESCRIPTION
		"The blacklist class name."
	::= { ltmFwIpintRouteDomainStatEntry 2 }

ltmFwIpintRouteDomainStatSrcIpBlacklist OBJECT-TYPE
	SYNTAX Counter64
	MAX-ACCESS read-only
	STATUS current
	DESCRIPTION
		"The number of packets whose source IP matched this category."
	::= { ltmFwIpintRouteDomainStatEntry 3 }

ltmFwIpintRouteDomainStatDstIpBlacklist OBJECT-TYPE
	SYNTAX Counter64
	MAX-ACCESS read-only
	STATUS current
	DESCRIPTION
		"The number of packets whose destination IP matched this category."
	::= { ltmFwIpintRouteDomainStatEntry 4 }

--==================================================================
-- Route_domain_stat
--==================================================================
ltmRouteDomainStatResetStats OBJECT-TYPE
	SYNTAX INTEGER
	MAX-ACCESS read-write
	STATUS current
	DESCRIPTION
		"The action to reset resettable statistics data in ltmRouteDomainStat.
		 Setting this value to 1 will reset statistics data.
		 Note, some statistics data may not be reset including data that are incremental counters."
	::= { ltmRouteDomainStat 1 }

ltmRouteDomainStatNumber OBJECT-TYPE
	SYNTAX INTEGER
	MAX-ACCESS read-only
	STATUS current
	DESCRIPTION
		"The number of ltmRouteDomainStat entries in the table."
	::= { ltmRouteDomainStat 2 }

ltmRouteDomainStatTable OBJECT-TYPE
	SYNTAX SEQUENCE OF LtmRouteDomainStatEntry
	MAX-ACCESS not-accessible
	STATUS current
	DESCRIPTION
		"A table containing statistic information of route domains."
	::= { ltmRouteDomainStat 3 }

ltmRouteDomainStatEntry OBJECT-TYPE
	SYNTAX  LtmRouteDomainStatEntry
	MAX-ACCESS not-accessible
	STATUS current
	DESCRIPTION
		"Columns in the ltmRouteDomainStat Table"
	INDEX {
		ltmRouteDomainStatName
	}
	::= { ltmRouteDomainStatTable 1 }

LtmRouteDomainStatEntry ::=
	SEQUENCE {
        	ltmRouteDomainStatName                                    LongDisplayString,
        	ltmRouteDomainStatConnLimit                               Gauge,
        	ltmRouteDomainStatConnectionFlowMiss                      Counter64,
        	ltmRouteDomainStatClientPktsIn                            Counter64,
        	ltmRouteDomainStatClientBytesIn                           Counter64,
        	ltmRouteDomainStatClientPktsOut                           Counter64,
        	ltmRouteDomainStatClientBytesOut                          Counter64,
        	ltmRouteDomainStatClientMaxConns                          Counter64,
        	ltmRouteDomainStatClientTotConns                          Counter64,
        	ltmRouteDomainStatClientCurConns                          Gauge,
        	ltmRouteDomainStatClientEvictedConns                      Counter64,
        	ltmRouteDomainStatClientSlowKilled                        Counter64,
        	ltmRouteDomainStatServerPktsIn                            Counter64,
        	ltmRouteDomainStatServerBytesIn                           Counter64,
        	ltmRouteDomainStatServerPktsOut                           Counter64,
        	ltmRouteDomainStatServerBytesOut                          Counter64,
        	ltmRouteDomainStatServerMaxConns                          Counter64,
        	ltmRouteDomainStatServerTotConns                          Counter64,
        	ltmRouteDomainStatServerCurConns                          Gauge,
        	ltmRouteDomainStatServerEvictedConns                      Counter64,
        	ltmRouteDomainStatServerSlowKilled                        Counter64
	}

ltmRouteDomainStatName OBJECT-TYPE
	SYNTAX LongDisplayString
	MAX-ACCESS read-only
	STATUS current
	DESCRIPTION
		"The name of a route domain."
	::= { ltmRouteDomainStatEntry 1 }

ltmRouteDomainStatConnLimit OBJECT-TYPE
	SYNTAX Gauge
	MAX-ACCESS read-only
	STATUS current
	DESCRIPTION
		"The maximum number of connections the specified route domain is allowed
	         to have open at one time."
	::= { ltmRouteDomainStatEntry 2 }

ltmRouteDomainStatConnectionFlowMiss OBJECT-TYPE
	SYNTAX Counter64
	MAX-ACCESS read-only
	STATUS current
	DESCRIPTION
		"The number of packets received that have no associated connection flow open."
	::= { ltmRouteDomainStatEntry 3 }

ltmRouteDomainStatClientPktsIn OBJECT-TYPE
	SYNTAX Counter64
	MAX-ACCESS read-only
	STATUS current
	DESCRIPTION
		"The number of packets received by the specified route domain from client-side."
	::= { ltmRouteDomainStatEntry 4 }

ltmRouteDomainStatClientBytesIn OBJECT-TYPE
	SYNTAX Counter64
	MAX-ACCESS read-only
	STATUS current
	DESCRIPTION
		"The number of bytes received by the specified route domain from client-side."
	::= { ltmRouteDomainStatEntry 5 }

ltmRouteDomainStatClientPktsOut OBJECT-TYPE
	SYNTAX Counter64
	MAX-ACCESS read-only
	STATUS current
	DESCRIPTION
		"The number of packets sent to client-side on the specified route domain."
	::= { ltmRouteDomainStatEntry 6 }

ltmRouteDomainStatClientBytesOut OBJECT-TYPE
	SYNTAX Counter64
	MAX-ACCESS read-only
	STATUS current
	DESCRIPTION
		"The number of bytes sent to client-side on the specified route domain."
	::= { ltmRouteDomainStatEntry 7 }

ltmRouteDomainStatClientMaxConns OBJECT-TYPE
	SYNTAX Counter64
	MAX-ACCESS read-only
	STATUS current
	DESCRIPTION
		"The maximum connections from client-side on the specified route domain."
	::= { ltmRouteDomainStatEntry 8 }

ltmRouteDomainStatClientTotConns OBJECT-TYPE
	SYNTAX Counter64
	MAX-ACCESS read-only
	STATUS current
	DESCRIPTION
		"The total connections from client-side on the specified route domain."
	::= { ltmRouteDomainStatEntry 9 }

ltmRouteDomainStatClientCurConns OBJECT-TYPE
	SYNTAX Gauge
	MAX-ACCESS read-only
	STATUS current
	DESCRIPTION
		"The current connections from client-side on the specified route domain."
	::= { ltmRouteDomainStatEntry 10 }

ltmRouteDomainStatClientEvictedConns OBJECT-TYPE
	SYNTAX Counter64
	MAX-ACCESS read-only
	STATUS current
	DESCRIPTION
		"The number of client-side connections that have been evicted on the specified route domain."
	::= { ltmRouteDomainStatEntry 11 }

ltmRouteDomainStatClientSlowKilled OBJECT-TYPE
	SYNTAX Counter64
	MAX-ACCESS read-only
	STATUS current
	DESCRIPTION
		"The number of slow client-side connections that have been killed on the specified route domain."
	::= { ltmRouteDomainStatEntry 12 }

ltmRouteDomainStatServerPktsIn OBJECT-TYPE
	SYNTAX Counter64
	MAX-ACCESS read-only
	STATUS current
	DESCRIPTION
		"The number of packets received by the specified route domain from server-side."
	::= { ltmRouteDomainStatEntry 13 }

ltmRouteDomainStatServerBytesIn OBJECT-TYPE
	SYNTAX Counter64
	MAX-ACCESS read-only
	STATUS current
	DESCRIPTION
		"The number of bytes received by the specified route domain from server-side."
	::= { ltmRouteDomainStatEntry 14 }

ltmRouteDomainStatServerPktsOut OBJECT-TYPE
	SYNTAX Counter64
	MAX-ACCESS read-only
	STATUS current
	DESCRIPTION
		"The number of packets sent to server-side on the specified route domain."
	::= { ltmRouteDomainStatEntry 15 }

ltmRouteDomainStatServerBytesOut OBJECT-TYPE
	SYNTAX Counter64
	MAX-ACCESS read-only
	STATUS current
	DESCRIPTION
		"The number of bytes sent to server-side on the specified route domain."
	::= { ltmRouteDomainStatEntry 16 }

ltmRouteDomainStatServerMaxConns OBJECT-TYPE
	SYNTAX Counter64
	MAX-ACCESS read-only
	STATUS current
	DESCRIPTION
		"The maximum connections from server-side on the specified route domain."
	::= { ltmRouteDomainStatEntry 17 }

ltmRouteDomainStatServerTotConns OBJECT-TYPE
	SYNTAX Counter64
	MAX-ACCESS read-only
	STATUS current
	DESCRIPTION
		"The total connections from server-side on the specified route domain."
	::= { ltmRouteDomainStatEntry 18 }

ltmRouteDomainStatServerCurConns OBJECT-TYPE
	SYNTAX Gauge
	MAX-ACCESS read-only
	STATUS current
	DESCRIPTION
		"The current connections from server-side on the specified route domain."
	::= { ltmRouteDomainStatEntry 19 }

ltmRouteDomainStatServerEvictedConns OBJECT-TYPE
	SYNTAX Counter64
	MAX-ACCESS read-only
	STATUS current
	DESCRIPTION
		"The number of server-side connections that have been evicted on the specified route domain."
	::= { ltmRouteDomainStatEntry 20 }

ltmRouteDomainStatServerSlowKilled OBJECT-TYPE
	SYNTAX Counter64
	MAX-ACCESS read-only
	STATUS current
	DESCRIPTION
		"The number of slow server-side connections that have been killed on the specified route domain."
	::= { ltmRouteDomainStatEntry 21 }

--==================================================================
-- Flow_eviction_policy_stat
--==================================================================
ltmFlowEvictionPolicyStatResetStats OBJECT-TYPE
	SYNTAX INTEGER
	MAX-ACCESS read-write
	STATUS current
	DESCRIPTION
		"The action to reset resettable statistics data in ltmFlowEvictionPolicyStat.
		 Setting this value to 1 will reset statistics data.
		 Note, some statistics data may not be reset including data that are incremental counters."
	::= { ltmFlowEvictionPolicyStat 1 }

ltmFlowEvictionPolicyStatNumber OBJECT-TYPE
	SYNTAX INTEGER
	MAX-ACCESS read-only
	STATUS current
	DESCRIPTION
		"The number of ltmFlowEvictionPolicyStat entries in the table."
	::= { ltmFlowEvictionPolicyStat 2 }

ltmFlowEvictionPolicyStatTable OBJECT-TYPE
	SYNTAX SEQUENCE OF LtmFlowEvictionPolicyStatEntry
	MAX-ACCESS not-accessible
	STATUS current
	DESCRIPTION
		"A table containing statistic information of flow eviction policies."
	::= { ltmFlowEvictionPolicyStat 3 }

ltmFlowEvictionPolicyStatEntry OBJECT-TYPE
	SYNTAX  LtmFlowEvictionPolicyStatEntry
	MAX-ACCESS not-accessible
	STATUS current
	DESCRIPTION
		"Columns in the ltmFlowEvictionPolicyStat Table"
	INDEX {
		ltmFlowEvictionPolicyStatPolicyName,
		ltmFlowEvictionPolicyStatSweptContext,
		ltmFlowEvictionPolicyStatContextName
	}
	::= { ltmFlowEvictionPolicyStatTable 1 }

LtmFlowEvictionPolicyStatEntry ::=
	SEQUENCE {
        	ltmFlowEvictionPolicyStatPolicyName                       LongDisplayString,
        	ltmFlowEvictionPolicyStatSweptContext                     LongDisplayString,
        	ltmFlowEvictionPolicyStatContextName                      LongDisplayString,
        	ltmFlowEvictionPolicyStatEvicted                          Counter64
	}

ltmFlowEvictionPolicyStatPolicyName OBJECT-TYPE
	SYNTAX LongDisplayString
	MAX-ACCESS read-only
	STATUS current
	DESCRIPTION
		"The policy name."
	::= { ltmFlowEvictionPolicyStatEntry 1 }

ltmFlowEvictionPolicyStatSweptContext OBJECT-TYPE
	SYNTAX LongDisplayString
	MAX-ACCESS read-only
	STATUS current
	DESCRIPTION
		"The context that was swept."
	::= { ltmFlowEvictionPolicyStatEntry 2 }

ltmFlowEvictionPolicyStatContextName OBJECT-TYPE
	SYNTAX LongDisplayString
	MAX-ACCESS read-only
	STATUS current
	DESCRIPTION
		"The context name."
	::= { ltmFlowEvictionPolicyStatEntry 3 }

ltmFlowEvictionPolicyStatEvicted OBJECT-TYPE
	SYNTAX Counter64
	MAX-ACCESS read-only
	STATUS current
	DESCRIPTION
		"The number of evicted flows."
	::= { ltmFlowEvictionPolicyStatEntry 4 }

--==================================================================
-- Alg_log_profile
--==================================================================
ltmAlgLogProfileNumber OBJECT-TYPE
	SYNTAX INTEGER
	MAX-ACCESS read-only
	STATUS current
	DESCRIPTION
		"The number of ltmAlgLogProfile entries in the table."
	::= { ltmAlgLogProfile 1 }

ltmAlgLogProfileTable OBJECT-TYPE
	SYNTAX SEQUENCE OF LtmAlgLogProfileEntry
	MAX-ACCESS not-accessible
	STATUS current
	DESCRIPTION
		"A table containing information about the ALG log profile."
	::= { ltmAlgLogProfile 2 }

ltmAlgLogProfileEntry OBJECT-TYPE
	SYNTAX  LtmAlgLogProfileEntry
	MAX-ACCESS not-accessible
	STATUS current
	DESCRIPTION
		"Columns in the ltmAlgLogProfile Table"
	INDEX {
		ltmAlgLogProfileName
	}
	::= { ltmAlgLogProfileTable 1 }

LtmAlgLogProfileEntry ::=
	SEQUENCE {
        	ltmAlgLogProfileName                                      LongDisplayString,
        	ltmAlgLogProfileDescription                               LongDisplayString,
        	ltmAlgLogProfileConfigSource                              INTEGER,
        	ltmAlgLogProfileDefaultName                               LongDisplayString,
        	ltmAlgLogProfileStartControlAction                        INTEGER,
        	ltmAlgLogProfileEndControlAction                          INTEGER,
        	ltmAlgLogProfileStartDataAction                           INTEGER,
        	ltmAlgLogProfileEndDataAction                             INTEGER,
        	ltmAlgLogProfileInboundAction                             INTEGER,
        	ltmAlgLogProfileCsvFormat                                 INTEGER
	}

ltmAlgLogProfileName OBJECT-TYPE
	SYNTAX LongDisplayString
	MAX-ACCESS read-only
	STATUS current
	DESCRIPTION
		"The name of a ALG Log profile."
	::= { ltmAlgLogProfileEntry 1 }

ltmAlgLogProfileDescription OBJECT-TYPE
	SYNTAX LongDisplayString
	MAX-ACCESS read-only
	STATUS current
	DESCRIPTION
		"The description of a ALG log profile."
	::= { ltmAlgLogProfileEntry 2 }

ltmAlgLogProfileConfigSource OBJECT-TYPE
	SYNTAX INTEGER {
		usercfg(0),
		basecfg(1)
	}
	MAX-ACCESS read-only
	STATUS current
	DESCRIPTION
		"The state that specifies whether this is a base/pre-configured profile
		or user defined profile."
	::= { ltmAlgLogProfileEntry 3 }

ltmAlgLogProfileDefaultName OBJECT-TYPE
	SYNTAX LongDisplayString
	MAX-ACCESS read-only
	STATUS current
	DESCRIPTION
		"The name of the profile from which the specified profile derives
		its attribute default values."
	::= { ltmAlgLogProfileEntry 4 }

ltmAlgLogProfileStartControlAction OBJECT-TYPE
	SYNTAX INTEGER {
		disabled(1),
		enabled(2),
		backupAllocationOnly(3)
	}
	MAX-ACCESS read-only
	STATUS current
	DESCRIPTION
		"Log action to occur at the creation of the control channel connection."
	::= { ltmAlgLogProfileEntry 5 }

ltmAlgLogProfileEndControlAction OBJECT-TYPE
	SYNTAX INTEGER {
		disabled(1),
		enabled(2),
		backupAllocationOnly(3)
	}
	MAX-ACCESS read-only
	STATUS current
	DESCRIPTION
		"Log action to occur at the end of the control channel connection."
	::= { ltmAlgLogProfileEntry 6 }

ltmAlgLogProfileStartDataAction OBJECT-TYPE
	SYNTAX INTEGER {
		disabled(1),
		enabled(2),
		backupAllocationOnly(3)
	}
	MAX-ACCESS read-only
	STATUS current
	DESCRIPTION
		"Log action to occur at the creation of the data channel connection."
	::= { ltmAlgLogProfileEntry 7 }

ltmAlgLogProfileEndDataAction OBJECT-TYPE
	SYNTAX INTEGER {
		disabled(1),
		enabled(2),
		backupAllocationOnly(3)
	}
	MAX-ACCESS read-only
	STATUS current
	DESCRIPTION
		"Log action to occur at the end of the data channel connection."
	::= { ltmAlgLogProfileEntry 8 }

ltmAlgLogProfileInboundAction OBJECT-TYPE
	SYNTAX INTEGER {
		disabled(1),
		enabled(2)
	}
	MAX-ACCESS read-only
	STATUS current
	DESCRIPTION
		"Log action to occur for inbound transactions, this could be either
		 incoming or outgoing message."
	::= { ltmAlgLogProfileEntry 9 }

ltmAlgLogProfileCsvFormat OBJECT-TYPE
	SYNTAX INTEGER {
		disabled(0),
		enabled(1)
	}
	MAX-ACCESS read-only
	STATUS current
	DESCRIPTION
		"Use CSV log format for output."
	::= { ltmAlgLogProfileEntry 10 }

--==================================================================
-- Alg_log_profile_start_control_elements
--==================================================================
ltmAlgLogProfileStartControlElementsNumber OBJECT-TYPE
	SYNTAX INTEGER
	MAX-ACCESS read-only
	STATUS current
	DESCRIPTION
		"The number of ltmAlgLogProfileStartControlElements entries in the table."
	::= { ltmAlgLogProfileStartControlElements 1 }

ltmAlgLogProfileStartControlElementsTable OBJECT-TYPE
	SYNTAX SEQUENCE OF LtmAlgLogProfileStartControlElementsEntry
	MAX-ACCESS not-accessible
	STATUS current
	DESCRIPTION
		"A table containing information on the optional elements of start control event log message."
	::= { ltmAlgLogProfileStartControlElements 2 }

ltmAlgLogProfileStartControlElementsEntry OBJECT-TYPE
	SYNTAX  LtmAlgLogProfileStartControlElementsEntry
	MAX-ACCESS not-accessible
	STATUS current
	DESCRIPTION
		"Columns in the ltmAlgLogProfileStartControlElements Table"
	INDEX {
		ltmAlgLogProfileStartControlElementsName,
		ltmAlgLogProfileStartControlElementsIndex
	}
	::= { ltmAlgLogProfileStartControlElementsTable 1 }

LtmAlgLogProfileStartControlElementsEntry ::=
	SEQUENCE {
        	ltmAlgLogProfileStartControlElementsName                  LongDisplayString,
        	ltmAlgLogProfileStartControlElementsIndex                 INTEGER,
        	ltmAlgLogProfileStartControlElementsElements              INTEGER
	}

ltmAlgLogProfileStartControlElementsName OBJECT-TYPE
	SYNTAX LongDisplayString
	MAX-ACCESS read-only
	STATUS current
	DESCRIPTION
		"The name of a ALG Log profile."
	::= { ltmAlgLogProfileStartControlElementsEntry 1 }

ltmAlgLogProfileStartControlElementsIndex OBJECT-TYPE
	SYNTAX INTEGER(0..2147483647)
	MAX-ACCESS read-only
	STATUS current
	DESCRIPTION
		"The index of the optional element for ALG event log messages."
	::= { ltmAlgLogProfileStartControlElementsEntry 2 }

ltmAlgLogProfileStartControlElementsElements OBJECT-TYPE
	SYNTAX INTEGER {
		destination(1)
	}
	MAX-ACCESS read-only
	STATUS current
	DESCRIPTION
		"The optional element of ALG event log messages."
	::= { ltmAlgLogProfileStartControlElementsEntry 3 }

--==================================================================
-- Alg_log_profile_end_control_elements
--==================================================================
ltmAlgLogProfileEndControlElementsNumber OBJECT-TYPE
	SYNTAX INTEGER
	MAX-ACCESS read-only
	STATUS current
	DESCRIPTION
		"The number of ltmAlgLogProfileEndControlElements entries in the table."
	::= { ltmAlgLogProfileEndControlElements 1 }

ltmAlgLogProfileEndControlElementsTable OBJECT-TYPE
	SYNTAX SEQUENCE OF LtmAlgLogProfileEndControlElementsEntry
	MAX-ACCESS not-accessible
	STATUS current
	DESCRIPTION
		"A table containing information on the optional elements of end control event log message."
	::= { ltmAlgLogProfileEndControlElements 2 }

ltmAlgLogProfileEndControlElementsEntry OBJECT-TYPE
	SYNTAX  LtmAlgLogProfileEndControlElementsEntry
	MAX-ACCESS not-accessible
	STATUS current
	DESCRIPTION
		"Columns in the ltmAlgLogProfileEndControlElements Table"
	INDEX {
		ltmAlgLogProfileEndControlElementsName,
		ltmAlgLogProfileEndControlElementsIndex
	}
	::= { ltmAlgLogProfileEndControlElementsTable 1 }

LtmAlgLogProfileEndControlElementsEntry ::=
	SEQUENCE {
        	ltmAlgLogProfileEndControlElementsName                    LongDisplayString,
        	ltmAlgLogProfileEndControlElementsIndex                   INTEGER,
        	ltmAlgLogProfileEndControlElementsElements                INTEGER
	}

ltmAlgLogProfileEndControlElementsName OBJECT-TYPE
	SYNTAX LongDisplayString
	MAX-ACCESS read-only
	STATUS current
	DESCRIPTION
		"The name of a ALG Log profile."
	::= { ltmAlgLogProfileEndControlElementsEntry 1 }

ltmAlgLogProfileEndControlElementsIndex OBJECT-TYPE
	SYNTAX INTEGER(0..2147483647)
	MAX-ACCESS read-only
	STATUS current
	DESCRIPTION
		"The index of the optional element for ALG event log messages."
	::= { ltmAlgLogProfileEndControlElementsEntry 2 }

ltmAlgLogProfileEndControlElementsElements OBJECT-TYPE
	SYNTAX INTEGER {
		destination(1)
	}
	MAX-ACCESS read-only
	STATUS current
	DESCRIPTION
		"The optional element of ALG event log messages."
	::= { ltmAlgLogProfileEndControlElementsEntry 3 }

--==================================================================
-- Alg_log_profile_start_data_elements
--==================================================================
ltmAlgLogProfileStartDataElementsNumber OBJECT-TYPE
	SYNTAX INTEGER
	MAX-ACCESS read-only
	STATUS current
	DESCRIPTION
		"The number of ltmAlgLogProfileStartDataElements entries in the table."
	::= { ltmAlgLogProfileStartDataElements 1 }

ltmAlgLogProfileStartDataElementsTable OBJECT-TYPE
	SYNTAX SEQUENCE OF LtmAlgLogProfileStartDataElementsEntry
	MAX-ACCESS not-accessible
	STATUS current
	DESCRIPTION
		"A table containing information on the optional elements of start data event log message."
	::= { ltmAlgLogProfileStartDataElements 2 }

ltmAlgLogProfileStartDataElementsEntry OBJECT-TYPE
	SYNTAX  LtmAlgLogProfileStartDataElementsEntry
	MAX-ACCESS not-accessible
	STATUS current
	DESCRIPTION
		"Columns in the ltmAlgLogProfileStartDataElements Table"
	INDEX {
		ltmAlgLogProfileStartDataElementsName,
		ltmAlgLogProfileStartDataElementsIndex
	}
	::= { ltmAlgLogProfileStartDataElementsTable 1 }

LtmAlgLogProfileStartDataElementsEntry ::=
	SEQUENCE {
        	ltmAlgLogProfileStartDataElementsName                     LongDisplayString,
        	ltmAlgLogProfileStartDataElementsIndex                    INTEGER,
        	ltmAlgLogProfileStartDataElementsElements                 INTEGER
	}

ltmAlgLogProfileStartDataElementsName OBJECT-TYPE
	SYNTAX LongDisplayString
	MAX-ACCESS read-only
	STATUS current
	DESCRIPTION
		"The name of a ALG Log profile."
	::= { ltmAlgLogProfileStartDataElementsEntry 1 }

ltmAlgLogProfileStartDataElementsIndex OBJECT-TYPE
	SYNTAX INTEGER(0..2147483647)
	MAX-ACCESS read-only
	STATUS current
	DESCRIPTION
		"The index of the optional element for ALG event log messages."
	::= { ltmAlgLogProfileStartDataElementsEntry 2 }

ltmAlgLogProfileStartDataElementsElements OBJECT-TYPE
	SYNTAX INTEGER {
		destination(1)
	}
	MAX-ACCESS read-only
	STATUS current
	DESCRIPTION
		"The optional element of ALG event log messages."
	::= { ltmAlgLogProfileStartDataElementsEntry 3 }

--==================================================================
-- Alg_log_profile_end_data_elements
--==================================================================
ltmAlgLogProfileEndDataElementsNumber OBJECT-TYPE
	SYNTAX INTEGER
	MAX-ACCESS read-only
	STATUS current
	DESCRIPTION
		"The number of ltmAlgLogProfileEndDataElements entries in the table."
	::= { ltmAlgLogProfileEndDataElements 1 }

ltmAlgLogProfileEndDataElementsTable OBJECT-TYPE
	SYNTAX SEQUENCE OF LtmAlgLogProfileEndDataElementsEntry
	MAX-ACCESS not-accessible
	STATUS current
	DESCRIPTION
		"A table containing information on the optional elements of end data event log message."
	::= { ltmAlgLogProfileEndDataElements 2 }

ltmAlgLogProfileEndDataElementsEntry OBJECT-TYPE
	SYNTAX  LtmAlgLogProfileEndDataElementsEntry
	MAX-ACCESS not-accessible
	STATUS current
	DESCRIPTION
		"Columns in the ltmAlgLogProfileEndDataElements Table"
	INDEX {
		ltmAlgLogProfileEndDataElementsName,
		ltmAlgLogProfileEndDataElementsIndex
	}
	::= { ltmAlgLogProfileEndDataElementsTable 1 }

LtmAlgLogProfileEndDataElementsEntry ::=
	SEQUENCE {
        	ltmAlgLogProfileEndDataElementsName                       LongDisplayString,
        	ltmAlgLogProfileEndDataElementsIndex                      INTEGER,
        	ltmAlgLogProfileEndDataElementsElements                   INTEGER
	}

ltmAlgLogProfileEndDataElementsName OBJECT-TYPE
	SYNTAX LongDisplayString
	MAX-ACCESS read-only
	STATUS current
	DESCRIPTION
		"The name of a ALG Log profile."
	::= { ltmAlgLogProfileEndDataElementsEntry 1 }

ltmAlgLogProfileEndDataElementsIndex OBJECT-TYPE
	SYNTAX INTEGER(0..2147483647)
	MAX-ACCESS read-only
	STATUS current
	DESCRIPTION
		"The index of the optional element for ALG event log messages."
	::= { ltmAlgLogProfileEndDataElementsEntry 2 }

ltmAlgLogProfileEndDataElementsElements OBJECT-TYPE
	SYNTAX INTEGER {
		destination(1)
	}
	MAX-ACCESS read-only
	STATUS current
	DESCRIPTION
		"The optional element of ALG event log messages."
	::= { ltmAlgLogProfileEndDataElementsEntry 3 }

--==================================================================
-- Lsn_log_profile
--==================================================================
ltmLsnLogProfileNumber OBJECT-TYPE
	SYNTAX INTEGER
	MAX-ACCESS read-only
	STATUS current
	DESCRIPTION
		"The number of ltmLsnLogProfile entries in the table."
	::= { ltmLsnLogProfile 1 }

ltmLsnLogProfileTable OBJECT-TYPE
	SYNTAX SEQUENCE OF LtmLsnLogProfileEntry
	MAX-ACCESS not-accessible
	STATUS current
	DESCRIPTION
		"A table containing information about the LSN log profile."
	::= { ltmLsnLogProfile 2 }

ltmLsnLogProfileEntry OBJECT-TYPE
	SYNTAX  LtmLsnLogProfileEntry
	MAX-ACCESS not-accessible
	STATUS current
	DESCRIPTION
		"Columns in the ltmLsnLogProfile Table"
	INDEX {
		ltmLsnLogProfileName
	}
	::= { ltmLsnLogProfileTable 1 }

LtmLsnLogProfileEntry ::=
	SEQUENCE {
        	ltmLsnLogProfileName                                      LongDisplayString,
        	ltmLsnLogProfileDescription                               LongDisplayString,
        	ltmLsnLogProfileConfigSource                              INTEGER,
        	ltmLsnLogProfileDefaultName                               LongDisplayString,
        	ltmLsnLogProfileStartOutboundAction                       INTEGER,
        	ltmLsnLogProfileEndOutboundAction                         INTEGER,
        	ltmLsnLogProfileStartInboundAction                        INTEGER,
        	ltmLsnLogProfileEndInboundAction                          INTEGER,
        	ltmLsnLogProfileQuotaExceededAction                       INTEGER,
        	ltmLsnLogProfileErrorsAction                              INTEGER,
        	ltmLsnLogProfileCsvFormat                                 INTEGER
	}

ltmLsnLogProfileName OBJECT-TYPE
	SYNTAX LongDisplayString
	MAX-ACCESS read-only
	STATUS current
	DESCRIPTION
		"The name of a ALG Log profile."
	::= { ltmLsnLogProfileEntry 1 }

ltmLsnLogProfileDescription OBJECT-TYPE
	SYNTAX LongDisplayString
	MAX-ACCESS read-only
	STATUS current
	DESCRIPTION
		"The description of a ALG log profile."
	::= { ltmLsnLogProfileEntry 2 }

ltmLsnLogProfileConfigSource OBJECT-TYPE
	SYNTAX INTEGER {
		usercfg(0),
		basecfg(1)
	}
	MAX-ACCESS read-only
	STATUS current
	DESCRIPTION
		"The state that specifies whether this is a base/pre-configured profile
		or user defined profile."
	::= { ltmLsnLogProfileEntry 3 }

ltmLsnLogProfileDefaultName OBJECT-TYPE
	SYNTAX LongDisplayString
	MAX-ACCESS read-only
	STATUS current
	DESCRIPTION
		"The name of the profile from which the specified profile derives
		its attribute default values."
	::= { ltmLsnLogProfileEntry 4 }

ltmLsnLogProfileStartOutboundAction OBJECT-TYPE
	SYNTAX INTEGER {
		disabled(1),
		enabled(2),
		backupAllocationOnly(3)
	}
	MAX-ACCESS read-only
	STATUS current
	DESCRIPTION
		"Log action to occur at the creation of the outbound LSN connection."
	::= { ltmLsnLogProfileEntry 5 }

ltmLsnLogProfileEndOutboundAction OBJECT-TYPE
	SYNTAX INTEGER {
		disabled(1),
		enabled(2),
		backupAllocationOnly(3)
	}
	MAX-ACCESS read-only
	STATUS current
	DESCRIPTION
		"Log action to occur at the end of the outbound LSN connection."
	::= { ltmLsnLogProfileEntry 6 }

ltmLsnLogProfileStartInboundAction OBJECT-TYPE
	SYNTAX INTEGER {
		disabled(1),
		enabled(2),
		backupAllocationOnly(3)
	}
	MAX-ACCESS read-only
	STATUS current
	DESCRIPTION
		"Log action to occur at the creation of the incoming connection."
	::= { ltmLsnLogProfileEntry 7 }

ltmLsnLogProfileEndInboundAction OBJECT-TYPE
	SYNTAX INTEGER {
		disabled(1),
		enabled(2),
		backupAllocationOnly(3)
	}
	MAX-ACCESS read-only
	STATUS current
	DESCRIPTION
		"Log action to occur at the end of the incoming connection."
	::= { ltmLsnLogProfileEntry 8 }

ltmLsnLogProfileQuotaExceededAction OBJECT-TYPE
	SYNTAX INTEGER {
		disabled(1),
		enabled(2)
	}
	MAX-ACCESS read-only
	STATUS current
	DESCRIPTION
		"Log action to occur when LSN client exceeded allocated resources."
	::= { ltmLsnLogProfileEntry 9 }

ltmLsnLogProfileErrorsAction OBJECT-TYPE
	SYNTAX INTEGER {
		disabled(1),
		enabled(2)
	}
	MAX-ACCESS read-only
	STATUS current
	DESCRIPTION
		"Log action to occur when LSN translation errors occur."
	::= { ltmLsnLogProfileEntry 10 }

ltmLsnLogProfileCsvFormat OBJECT-TYPE
	SYNTAX INTEGER {
		disabled(0),
		enabled(1)
	}
	MAX-ACCESS read-only
	STATUS current
	DESCRIPTION
		"Use CSV log format for output."
	::= { ltmLsnLogProfileEntry 11 }

--==================================================================
-- Lsn_log_profile_start_outbound_elements
--==================================================================
ltmLsnLogProfileStartOutboundElementsNumber OBJECT-TYPE
	SYNTAX INTEGER
	MAX-ACCESS read-only
	STATUS current
	DESCRIPTION
		"The number of ltmLsnLogProfileStartOutboundElements entries in the table."
	::= { ltmLsnLogProfileStartOutboundElements 1 }

ltmLsnLogProfileStartOutboundElementsTable OBJECT-TYPE
	SYNTAX SEQUENCE OF LtmLsnLogProfileStartOutboundElementsEntry
	MAX-ACCESS not-accessible
	STATUS current
	DESCRIPTION
		"A table containing information on the optional elements of start outbound event log message."
	::= { ltmLsnLogProfileStartOutboundElements 2 }

ltmLsnLogProfileStartOutboundElementsEntry OBJECT-TYPE
	SYNTAX  LtmLsnLogProfileStartOutboundElementsEntry
	MAX-ACCESS not-accessible
	STATUS current
	DESCRIPTION
		"Columns in the ltmLsnLogProfileStartOutboundElements Table"
	INDEX {
		ltmLsnLogProfileStartOutboundElementsName,
		ltmLsnLogProfileStartOutboundElementsIndex
	}
	::= { ltmLsnLogProfileStartOutboundElementsTable 1 }

LtmLsnLogProfileStartOutboundElementsEntry ::=
	SEQUENCE {
        	ltmLsnLogProfileStartOutboundElementsName                 LongDisplayString,
        	ltmLsnLogProfileStartOutboundElementsIndex                INTEGER,
        	ltmLsnLogProfileStartOutboundElementsElements             INTEGER
	}

ltmLsnLogProfileStartOutboundElementsName OBJECT-TYPE
	SYNTAX LongDisplayString
	MAX-ACCESS read-only
	STATUS current
	DESCRIPTION
		"The name of a LSN Log profile."
	::= { ltmLsnLogProfileStartOutboundElementsEntry 1 }

ltmLsnLogProfileStartOutboundElementsIndex OBJECT-TYPE
	SYNTAX INTEGER(0..2147483647)
	MAX-ACCESS read-only
	STATUS current
	DESCRIPTION
		"The index of the optional element for LSN log messages."
	::= { ltmLsnLogProfileStartOutboundElementsEntry 2 }

ltmLsnLogProfileStartOutboundElementsElements OBJECT-TYPE
	SYNTAX INTEGER {
		destination(1)
	}
	MAX-ACCESS read-only
	STATUS current
	DESCRIPTION
		"The optional element of LSN log messages."
	::= { ltmLsnLogProfileStartOutboundElementsEntry 3 }

--==================================================================
-- Lsn_log_profile_end_outbound_elements
--==================================================================
ltmLsnLogProfileEndOutboundElementsNumber OBJECT-TYPE
	SYNTAX INTEGER
	MAX-ACCESS read-only
	STATUS current
	DESCRIPTION
		"The number of ltmLsnLogProfileEndOutboundElements entries in the table."
	::= { ltmLsnLogProfileEndOutboundElements 1 }

ltmLsnLogProfileEndOutboundElementsTable OBJECT-TYPE
	SYNTAX SEQUENCE OF LtmLsnLogProfileEndOutboundElementsEntry
	MAX-ACCESS not-accessible
	STATUS current
	DESCRIPTION
		"A table containing information on the optional elements of end outbound event log message."
	::= { ltmLsnLogProfileEndOutboundElements 2 }

ltmLsnLogProfileEndOutboundElementsEntry OBJECT-TYPE
	SYNTAX  LtmLsnLogProfileEndOutboundElementsEntry
	MAX-ACCESS not-accessible
	STATUS current
	DESCRIPTION
		"Columns in the ltmLsnLogProfileEndOutboundElements Table"
	INDEX {
		ltmLsnLogProfileEndOutboundElementsName,
		ltmLsnLogProfileEndOutboundElementsIndex
	}
	::= { ltmLsnLogProfileEndOutboundElementsTable 1 }

LtmLsnLogProfileEndOutboundElementsEntry ::=
	SEQUENCE {
        	ltmLsnLogProfileEndOutboundElementsName                   LongDisplayString,
        	ltmLsnLogProfileEndOutboundElementsIndex                  INTEGER,
        	ltmLsnLogProfileEndOutboundElementsElements               INTEGER
	}

ltmLsnLogProfileEndOutboundElementsName OBJECT-TYPE
	SYNTAX LongDisplayString
	MAX-ACCESS read-only
	STATUS current
	DESCRIPTION
		"The name of a LSN Log profile."
	::= { ltmLsnLogProfileEndOutboundElementsEntry 1 }

ltmLsnLogProfileEndOutboundElementsIndex OBJECT-TYPE
	SYNTAX INTEGER(0..2147483647)
	MAX-ACCESS read-only
	STATUS current
	DESCRIPTION
		"The index of the optional element for LSN log messages."
	::= { ltmLsnLogProfileEndOutboundElementsEntry 2 }

ltmLsnLogProfileEndOutboundElementsElements OBJECT-TYPE
	SYNTAX INTEGER {
		destination(1)
	}
	MAX-ACCESS read-only
	STATUS current
	DESCRIPTION
		"The optional element of LSN log messages."
	::= { ltmLsnLogProfileEndOutboundElementsEntry 3 }

--==================================================================
-- Ocsp_stapling_params
--==================================================================
ltmOcspStaplingParametersNumber OBJECT-TYPE
	SYNTAX INTEGER
	MAX-ACCESS read-only
	STATUS current
	DESCRIPTION
		"The number of ltmOcspStaplingParameters entries in the table."
	::= { ltmOcspStaplingParameters 1 }

ltmOcspStaplingParametersTable OBJECT-TYPE
	SYNTAX SEQUENCE OF LtmOcspStaplingParametersEntry
	MAX-ACCESS not-accessible
	STATUS current
	DESCRIPTION
		"A table containing options to be used for enabling OCSP Stapling on clientside SSL profiles."
	::= { ltmOcspStaplingParameters 2 }

ltmOcspStaplingParametersEntry OBJECT-TYPE
	SYNTAX  LtmOcspStaplingParametersEntry
	MAX-ACCESS not-accessible
	STATUS current
	DESCRIPTION
		"Columns in the ltmOcspStaplingParameters Table"
	INDEX {
		ltmOcspStaplingParametersName
	}
	::= { ltmOcspStaplingParametersTable 1 }

LtmOcspStaplingParametersEntry ::=
	SEQUENCE {
        	ltmOcspStaplingParametersName                             LongDisplayString,
        	ltmOcspStaplingParametersUseProxyServer                   INTEGER,
        	ltmOcspStaplingParametersProxyServerPool                  LongDisplayString,
        	ltmOcspStaplingParametersDnsResolver                      LongDisplayString,
        	ltmOcspStaplingParametersTrustedCa                        LongDisplayString,
        	ltmOcspStaplingParametersTrustedResponders                LongDisplayString,
        	ltmOcspStaplingParametersUrl                              LongDisplayString,
        	ltmOcspStaplingParametersSignerCert                       LongDisplayString,
        	ltmOcspStaplingParametersSignerKey                        LongDisplayString,
        	ltmOcspStaplingParametersSignHash                         INTEGER,
        	ltmOcspStaplingParametersTimeout                          Gauge,
        	ltmOcspStaplingParametersClockSkew                        Gauge,
        	ltmOcspStaplingParametersStatusAge                        Gauge,
        	ltmOcspStaplingParametersCacheTimeout                     Gauge,
        	ltmOcspStaplingParametersCacheErrorTimeout                Gauge,
        	ltmOcspStaplingParametersStrictRespCertCheck              INTEGER
	}

ltmOcspStaplingParametersName OBJECT-TYPE
	SYNTAX LongDisplayString
	MAX-ACCESS read-only
	STATUS current
	DESCRIPTION
		"The name of the OCSP Stapling Parameters object."
	::= { ltmOcspStaplingParametersEntry 1 }

ltmOcspStaplingParametersUseProxyServer OBJECT-TYPE
	SYNTAX INTEGER {
		false(0),
		true(1)
	}
	MAX-ACCESS read-only
	STATUS current
	DESCRIPTION
		"Whether to use a proxy server or a DNS resolver."
	::= { ltmOcspStaplingParametersEntry 2 }

ltmOcspStaplingParametersProxyServerPool OBJECT-TYPE
	SYNTAX LongDisplayString
	MAX-ACCESS read-only
	STATUS current
	DESCRIPTION
		"The name of the proxy server pool."
	::= { ltmOcspStaplingParametersEntry 3 }

ltmOcspStaplingParametersDnsResolver OBJECT-TYPE
	SYNTAX LongDisplayString
	MAX-ACCESS read-only
	STATUS current
	DESCRIPTION
		"The name of the DNS resolver."
	::= { ltmOcspStaplingParametersEntry 4 }

ltmOcspStaplingParametersTrustedCa OBJECT-TYPE
	SYNTAX LongDisplayString
	MAX-ACCESS read-only
	STATUS current
	DESCRIPTION
		"The name of the trusted certificate authority file."
	::= { ltmOcspStaplingParametersEntry 5 }

ltmOcspStaplingParametersTrustedResponders OBJECT-TYPE
	SYNTAX LongDisplayString
	MAX-ACCESS read-only
	STATUS current
	DESCRIPTION
		"The name of the file containing the trusted OCSP responders."
	::= { ltmOcspStaplingParametersEntry 6 }

ltmOcspStaplingParametersUrl OBJECT-TYPE
	SYNTAX LongDisplayString
	MAX-ACCESS read-only
	STATUS current
	DESCRIPTION
		"The name of the responder URL."
	::= { ltmOcspStaplingParametersEntry 7 }

ltmOcspStaplingParametersSignerCert OBJECT-TYPE
	SYNTAX LongDisplayString
	MAX-ACCESS read-only
	STATUS current
	DESCRIPTION
		"The name of the signer certificate file."
	::= { ltmOcspStaplingParametersEntry 8 }

ltmOcspStaplingParametersSignerKey OBJECT-TYPE
	SYNTAX LongDisplayString
	MAX-ACCESS read-only
	STATUS current
	DESCRIPTION
		"The name of the signer key file."
	::= { ltmOcspStaplingParametersEntry 9 }

ltmOcspStaplingParametersSignHash OBJECT-TYPE
	SYNTAX INTEGER {
		sha1(0),
		sha256(1)
	}
	MAX-ACCESS read-only
	STATUS current
	DESCRIPTION
		"The hash algorithm used for signing the OCSP request."
	::= { ltmOcspStaplingParametersEntry 10 }

ltmOcspStaplingParametersTimeout OBJECT-TYPE
	SYNTAX Gauge
	MAX-ACCESS read-only
	STATUS current
	DESCRIPTION
		"The OCSP Stapling timeout."
	::= { ltmOcspStaplingParametersEntry 11 }

ltmOcspStaplingParametersClockSkew OBJECT-TYPE
	SYNTAX Gauge
	MAX-ACCESS read-only
	STATUS current
	DESCRIPTION
		"The maximum allowable clock skew between the BIG-IP and the OCSP responder."
	::= { ltmOcspStaplingParametersEntry 12 }

ltmOcspStaplingParametersStatusAge OBJECT-TYPE
	SYNTAX Gauge
	MAX-ACCESS read-only
	STATUS current
	DESCRIPTION
		"The allowed age of the OCSP response when nextUpdate time is not specified in the response."
	::= { ltmOcspStaplingParametersEntry 13 }

ltmOcspStaplingParametersCacheTimeout OBJECT-TYPE
	SYNTAX Gauge
	MAX-ACCESS read-only
	STATUS current
	DESCRIPTION
		"The desired lifetime of the OCSP response in the cache, in seconds."
	::= { ltmOcspStaplingParametersEntry 14 }

ltmOcspStaplingParametersCacheErrorTimeout OBJECT-TYPE
	SYNTAX Gauge
	MAX-ACCESS read-only
	STATUS current
	DESCRIPTION
		"The lifetime of an error response in the cache, in seconds."
	::= { ltmOcspStaplingParametersEntry 15 }

ltmOcspStaplingParametersStrictRespCertCheck OBJECT-TYPE
	SYNTAX INTEGER {
		false(0),
		true(1)
	}
	MAX-ACCESS read-only
	STATUS current
	DESCRIPTION
		"Whether the certificate in the OCSP response should be checked for OCSP signing extension."
	::= { ltmOcspStaplingParametersEntry 16 }

--==================================================================
-- Fw_rule_stat
--==================================================================
ltmFwRuleStatNumber OBJECT-TYPE
	SYNTAX INTEGER
	MAX-ACCESS read-only
	STATUS current
	DESCRIPTION
		"The number of ltmFwRuleStat entries in the table."
	::= { ltmFwRuleStat 1 }

ltmFwRuleStatTable OBJECT-TYPE
	SYNTAX SEQUENCE OF LtmFwRuleStatEntry
	MAX-ACCESS not-accessible
	STATUS current
	DESCRIPTION
		"A table containing statistic information of Firewall rule stats."
	::= { ltmFwRuleStat 2 }

ltmFwRuleStatEntry OBJECT-TYPE
	SYNTAX  LtmFwRuleStatEntry
	MAX-ACCESS not-accessible
	STATUS current
	DESCRIPTION
		"Columns in the ltmFwRuleStat Table"
	INDEX {
		ltmFwRuleStatContextType,
		ltmFwRuleStatContextName,
		ltmFwRuleStatRuleName,
		ltmFwRuleStatRuleListName,
		ltmFwRuleStatPolicyName,
		ltmFwRuleStatRuleStatType
	}
	::= { ltmFwRuleStatTable 1 }

LtmFwRuleStatEntry ::=
	SEQUENCE {
        	ltmFwRuleStatContextType                                  LongDisplayString,
        	ltmFwRuleStatContextName                                  LongDisplayString,
        	ltmFwRuleStatRuleName                                     LongDisplayString,
        	ltmFwRuleStatRuleListName                                 LongDisplayString,
        	ltmFwRuleStatPolicyName                                   LongDisplayString,
        	ltmFwRuleStatRuleStatType                                 INTEGER,
        	ltmFwRuleStatActualRule                                   LongDisplayString,
        	ltmFwRuleStatCounter                                      Counter64,
        	ltmFwRuleStatLastHitTime                                  Counter64,
        	ltmFwRuleStatLastHitTimeFmt                               LongDisplayString,
        	ltmFwRuleStatOverlapper                                   LongDisplayString,
        	ltmFwRuleStatOverlapType                                  LongDisplayString,
        	ltmFwRuleStatAction                                       INTEGER
	}

ltmFwRuleStatContextType OBJECT-TYPE
	SYNTAX LongDisplayString
	MAX-ACCESS read-only
	STATUS current
	DESCRIPTION
		"The context type."
	::= { ltmFwRuleStatEntry 1 }

ltmFwRuleStatContextName OBJECT-TYPE
	SYNTAX LongDisplayString
	MAX-ACCESS read-only
	STATUS current
	DESCRIPTION
		"The context name."
	::= { ltmFwRuleStatEntry 2 }

ltmFwRuleStatRuleName OBJECT-TYPE
	SYNTAX LongDisplayString
	MAX-ACCESS read-only
	STATUS current
	DESCRIPTION
		"The rule name."
	::= { ltmFwRuleStatEntry 3 }

ltmFwRuleStatRuleListName OBJECT-TYPE
	SYNTAX LongDisplayString
	MAX-ACCESS read-only
	STATUS current
	DESCRIPTION
		"The rule list name."
	::= { ltmFwRuleStatEntry 4 }

ltmFwRuleStatPolicyName OBJECT-TYPE
	SYNTAX LongDisplayString
	MAX-ACCESS read-only
	STATUS current
	DESCRIPTION
		"The policy name."
	::= { ltmFwRuleStatEntry 5 }

ltmFwRuleStatRuleStatType OBJECT-TYPE
	SYNTAX INTEGER {
		enforced(1),
		staged(2),
		active(3),
		overlapper(4)
	}
	MAX-ACCESS read-only
	STATUS current
	DESCRIPTION
		""
	::= { ltmFwRuleStatEntry 6 }

ltmFwRuleStatActualRule OBJECT-TYPE
	SYNTAX LongDisplayString
	MAX-ACCESS read-only
	STATUS current
	DESCRIPTION
		"The actual rule name."
	::= { ltmFwRuleStatEntry 7 }

ltmFwRuleStatCounter OBJECT-TYPE
	SYNTAX Counter64
	MAX-ACCESS read-only
	STATUS current
	DESCRIPTION
		"The number of packets matching this rule."
	::= { ltmFwRuleStatEntry 8 }

ltmFwRuleStatLastHitTime OBJECT-TYPE
	SYNTAX Counter64
	MAX-ACCESS read-only
	STATUS current
	DESCRIPTION
		"The last time a packet matched this rule."
	::= { ltmFwRuleStatEntry 9 }

ltmFwRuleStatLastHitTimeFmt OBJECT-TYPE
	SYNTAX LongDisplayString
	MAX-ACCESS read-only
	STATUS current
	DESCRIPTION
		"The last time a packet matched this rule, in human readable format."
	::= { ltmFwRuleStatEntry 10 }

ltmFwRuleStatOverlapper OBJECT-TYPE
	SYNTAX LongDisplayString
	MAX-ACCESS read-only
	STATUS current
	DESCRIPTION
		"The overlapper for this rule."
	::= { ltmFwRuleStatEntry 11 }

ltmFwRuleStatOverlapType OBJECT-TYPE
	SYNTAX LongDisplayString
	MAX-ACCESS read-only
	STATUS current
	DESCRIPTION
		"The overlap type."
	::= { ltmFwRuleStatEntry 12 }

ltmFwRuleStatAction OBJECT-TYPE
	SYNTAX INTEGER {
		accept(0),
		acceptDecisively(1),
		reject(2),
		drop(3)
	}
	MAX-ACCESS read-only
	STATUS current
	DESCRIPTION
		"The rule action"
	::= { ltmFwRuleStatEntry 13 }

--==================================================================
-- Fw_context_stat
--==================================================================
ltmFwContextStatNumber OBJECT-TYPE
	SYNTAX INTEGER
	MAX-ACCESS read-only
	STATUS current
	DESCRIPTION
		"The number of ltmFwContextStat entries in the table."
	::= { ltmFwContextStat 1 }

ltmFwContextStatTable OBJECT-TYPE
	SYNTAX SEQUENCE OF LtmFwContextStatEntry
	MAX-ACCESS not-accessible
	STATUS current
	DESCRIPTION
		"A table containing statistic information of Firewall context stats."
	::= { ltmFwContextStat 2 }

ltmFwContextStatEntry OBJECT-TYPE
	SYNTAX  LtmFwContextStatEntry
	MAX-ACCESS not-accessible
	STATUS current
	DESCRIPTION
		"Columns in the ltmFwContextStat Table"
	INDEX {
		ltmFwContextStatContextType,
		ltmFwContextStatContextName
	}
	::= { ltmFwContextStatTable 1 }

LtmFwContextStatEntry ::=
	SEQUENCE {
        	ltmFwContextStatContextType                               LongDisplayString,
        	ltmFwContextStatContextName                               LongDisplayString,
        	ltmFwContextStatEnforcedPacketsAccept                     Counter64,
        	ltmFwContextStatEnforcedPacketsAcceptDecisively           Counter64,
        	ltmFwContextStatEnforcedPacketsReject                     Counter64,
        	ltmFwContextStatEnforcedPacketsDrop                       Counter64,
        	ltmFwContextStatEnforcedPacketsDefaultAccept              Counter64,
        	ltmFwContextStatEnforcedPacketsDefaultReject              Counter64,
        	ltmFwContextStatEnforcedPacketsDefaultDrop                Counter64,
        	ltmFwContextStatStagedPacketsAccept                       Counter64,
        	ltmFwContextStatStagedPacketsAcceptDecisively             Counter64,
        	ltmFwContextStatStagedPacketsReject                       Counter64,
        	ltmFwContextStatStagedPacketsDrop                         Counter64,
        	ltmFwContextStatStagedPacketsDefaultAccept                Counter64,
        	ltmFwContextStatStagedPacketsDefaultReject                Counter64,
        	ltmFwContextStatStagedPacketsDefaultDrop                  Counter64
	}

ltmFwContextStatContextType OBJECT-TYPE
	SYNTAX LongDisplayString
	MAX-ACCESS read-only
	STATUS current
	DESCRIPTION
		"The context type."
	::= { ltmFwContextStatEntry 1 }

ltmFwContextStatContextName OBJECT-TYPE
	SYNTAX LongDisplayString
	MAX-ACCESS read-only
	STATUS current
	DESCRIPTION
		"The context name."
	::= { ltmFwContextStatEntry 2 }

ltmFwContextStatEnforcedPacketsAccept OBJECT-TYPE
	SYNTAX Counter64
	MAX-ACCESS read-only
	STATUS current
	DESCRIPTION
		"The number of packets accepted by enforced policy of this context."
	::= { ltmFwContextStatEntry 3 }

ltmFwContextStatEnforcedPacketsAcceptDecisively OBJECT-TYPE
	SYNTAX Counter64
	MAX-ACCESS read-only
	STATUS current
	DESCRIPTION
		"The number of packets accepted-decisively by enforced policy of this context."
	::= { ltmFwContextStatEntry 4 }

ltmFwContextStatEnforcedPacketsReject OBJECT-TYPE
	SYNTAX Counter64
	MAX-ACCESS read-only
	STATUS current
	DESCRIPTION
		"The number of packets rejected by enforced policy of this context."
	::= { ltmFwContextStatEntry 5 }

ltmFwContextStatEnforcedPacketsDrop OBJECT-TYPE
	SYNTAX Counter64
	MAX-ACCESS read-only
	STATUS current
	DESCRIPTION
		"The number of packets dropped by enforced policy of this context."
	::= { ltmFwContextStatEntry 6 }

ltmFwContextStatEnforcedPacketsDefaultAccept OBJECT-TYPE
	SYNTAX Counter64
	MAX-ACCESS read-only
	STATUS current
	DESCRIPTION
		"The number of packets accepted by default rule of enforced policy of this context."
	::= { ltmFwContextStatEntry 7 }

ltmFwContextStatEnforcedPacketsDefaultReject OBJECT-TYPE
	SYNTAX Counter64
	MAX-ACCESS read-only
	STATUS current
	DESCRIPTION
		"The number of packets rejected by default rule of enforced policy of this context."
	::= { ltmFwContextStatEntry 8 }

ltmFwContextStatEnforcedPacketsDefaultDrop OBJECT-TYPE
	SYNTAX Counter64
	MAX-ACCESS read-only
	STATUS current
	DESCRIPTION
		"The number of packets dropped by default rule of enforced policy of this context."
	::= { ltmFwContextStatEntry 9 }

ltmFwContextStatStagedPacketsAccept OBJECT-TYPE
	SYNTAX Counter64
	MAX-ACCESS read-only
	STATUS current
	DESCRIPTION
		"The number of packets accepted by staged policy of this context."
	::= { ltmFwContextStatEntry 10 }

ltmFwContextStatStagedPacketsAcceptDecisively OBJECT-TYPE
	SYNTAX Counter64
	MAX-ACCESS read-only
	STATUS current
	DESCRIPTION
		"The number of packets accepted-decisively by staged policy of this context."
	::= { ltmFwContextStatEntry 11 }

ltmFwContextStatStagedPacketsReject OBJECT-TYPE
	SYNTAX Counter64
	MAX-ACCESS read-only
	STATUS current
	DESCRIPTION
		"The number of packets rejected by staged policy of this context."
	::= { ltmFwContextStatEntry 12 }

ltmFwContextStatStagedPacketsDrop OBJECT-TYPE
	SYNTAX Counter64
	MAX-ACCESS read-only
	STATUS current
	DESCRIPTION
		"The number of packets dropped by staged policy of this context."
	::= { ltmFwContextStatEntry 13 }

ltmFwContextStatStagedPacketsDefaultAccept OBJECT-TYPE
	SYNTAX Counter64
	MAX-ACCESS read-only
	STATUS current
	DESCRIPTION
		"The number of packets accepted by default rule of staged policy of this context."
	::= { ltmFwContextStatEntry 14 }

ltmFwContextStatStagedPacketsDefaultReject OBJECT-TYPE
	SYNTAX Counter64
	MAX-ACCESS read-only
	STATUS current
	DESCRIPTION
		"The number of packets rejected by default rule of staged policy of this context."
	::= { ltmFwContextStatEntry 15 }

ltmFwContextStatStagedPacketsDefaultDrop OBJECT-TYPE
	SYNTAX Counter64
	MAX-ACCESS read-only
	STATUS current
	DESCRIPTION
		"The number of packets dropped by default rule of staged policy of this context."
	::= { ltmFwContextStatEntry 16 }

--==================================================================
-- Fw_policy_rule_stat
--==================================================================
ltmFwPolicyRuleStatNumber OBJECT-TYPE
	SYNTAX INTEGER
	MAX-ACCESS read-only
	STATUS current
	DESCRIPTION
		"The number of ltmFwPolicyRuleStat entries in the table."
	::= { ltmFwPolicyRuleStat 1 }

ltmFwPolicyRuleStatTable OBJECT-TYPE
	SYNTAX SEQUENCE OF LtmFwPolicyRuleStatEntry
	MAX-ACCESS not-accessible
	STATUS current
	DESCRIPTION
		"A table containing statistic information of Firewall policy rule stats."
	::= { ltmFwPolicyRuleStat 2 }

ltmFwPolicyRuleStatEntry OBJECT-TYPE
	SYNTAX  LtmFwPolicyRuleStatEntry
	MAX-ACCESS not-accessible
	STATUS current
	DESCRIPTION
		"Columns in the ltmFwPolicyRuleStat Table"
	INDEX {
		ltmFwPolicyRuleStatContextType,
		ltmFwPolicyRuleStatContextName,
		ltmFwPolicyRuleStatRuleName,
		ltmFwPolicyRuleStatRuleListName,
		ltmFwPolicyRuleStatPolicyName,
		ltmFwPolicyRuleStatRuleStatType
	}
	::= { ltmFwPolicyRuleStatTable 1 }

LtmFwPolicyRuleStatEntry ::=
	SEQUENCE {
        	ltmFwPolicyRuleStatContextType                            LongDisplayString,
        	ltmFwPolicyRuleStatContextName                            LongDisplayString,
        	ltmFwPolicyRuleStatRuleName                               LongDisplayString,
        	ltmFwPolicyRuleStatRuleListName                           LongDisplayString,
        	ltmFwPolicyRuleStatPolicyName                             LongDisplayString,
        	ltmFwPolicyRuleStatRuleStatType                           INTEGER,
        	ltmFwPolicyRuleStatActualRule                             LongDisplayString,
        	ltmFwPolicyRuleStatCounter                                Counter64,
        	ltmFwPolicyRuleStatLastHitTime                            Counter64,
        	ltmFwPolicyRuleStatLastHitTimeFmt                         LongDisplayString,
        	ltmFwPolicyRuleStatOverlapper                             LongDisplayString,
        	ltmFwPolicyRuleStatOverlapType                            LongDisplayString
	}

ltmFwPolicyRuleStatContextType OBJECT-TYPE
	SYNTAX LongDisplayString
	MAX-ACCESS read-only
	STATUS current
	DESCRIPTION
		"The context type."
	::= { ltmFwPolicyRuleStatEntry 1 }

ltmFwPolicyRuleStatContextName OBJECT-TYPE
	SYNTAX LongDisplayString
	MAX-ACCESS read-only
	STATUS current
	DESCRIPTION
		"The context name."
	::= { ltmFwPolicyRuleStatEntry 2 }

ltmFwPolicyRuleStatRuleName OBJECT-TYPE
	SYNTAX LongDisplayString
	MAX-ACCESS read-only
	STATUS current
	DESCRIPTION
		"The rule name."
	::= { ltmFwPolicyRuleStatEntry 3 }

ltmFwPolicyRuleStatRuleListName OBJECT-TYPE
	SYNTAX LongDisplayString
	MAX-ACCESS read-only
	STATUS current
	DESCRIPTION
		"The rule list name."
	::= { ltmFwPolicyRuleStatEntry 4 }

ltmFwPolicyRuleStatPolicyName OBJECT-TYPE
	SYNTAX LongDisplayString
	MAX-ACCESS read-only
	STATUS current
	DESCRIPTION
		"The policy name."
	::= { ltmFwPolicyRuleStatEntry 5 }

ltmFwPolicyRuleStatRuleStatType OBJECT-TYPE
	SYNTAX INTEGER {
		enforced(1),
		staged(2),
		active(3),
		overlapper(4)
	}
	MAX-ACCESS read-only
	STATUS current
	DESCRIPTION
		""
	::= { ltmFwPolicyRuleStatEntry 6 }

ltmFwPolicyRuleStatActualRule OBJECT-TYPE
	SYNTAX LongDisplayString
	MAX-ACCESS read-only
	STATUS current
	DESCRIPTION
		"The actual rule name."
	::= { ltmFwPolicyRuleStatEntry 7 }

ltmFwPolicyRuleStatCounter OBJECT-TYPE
	SYNTAX Counter64
	MAX-ACCESS read-only
	STATUS current
	DESCRIPTION
		"The number of packets matching this rule."
	::= { ltmFwPolicyRuleStatEntry 8 }

ltmFwPolicyRuleStatLastHitTime OBJECT-TYPE
	SYNTAX Counter64
	MAX-ACCESS read-only
	STATUS current
	DESCRIPTION
		"The last time a packet matched this rule."
	::= { ltmFwPolicyRuleStatEntry 9 }

ltmFwPolicyRuleStatLastHitTimeFmt OBJECT-TYPE
	SYNTAX LongDisplayString
	MAX-ACCESS read-only
	STATUS current
	DESCRIPTION
		"The last time a packet matched this rule, in human readable format."
	::= { ltmFwPolicyRuleStatEntry 10 }

ltmFwPolicyRuleStatOverlapper OBJECT-TYPE
	SYNTAX LongDisplayString
	MAX-ACCESS read-only
	STATUS current
	DESCRIPTION
		"The overlapper for this rule."
	::= { ltmFwPolicyRuleStatEntry 11 }

ltmFwPolicyRuleStatOverlapType OBJECT-TYPE
	SYNTAX LongDisplayString
	MAX-ACCESS read-only
	STATUS current
	DESCRIPTION
		"The overlap type."
	::= { ltmFwPolicyRuleStatEntry 12 }

--==================================================================
-- Profile_tftp
--==================================================================
ltmTftpProfileNumber OBJECT-TYPE
	SYNTAX INTEGER
	MAX-ACCESS read-only
	STATUS current
	DESCRIPTION
		"The number of ltmTftpProfile entries in the table."
	::= { ltmTftpProfile 1 }

ltmTftpProfileTable OBJECT-TYPE
	SYNTAX SEQUENCE OF LtmTftpProfileEntry
	MAX-ACCESS not-accessible
	STATUS current
	DESCRIPTION
		"A table containing information for TFTP profiles."
	::= { ltmTftpProfile 2 }

ltmTftpProfileEntry OBJECT-TYPE
	SYNTAX  LtmTftpProfileEntry
	MAX-ACCESS not-accessible
	STATUS current
	DESCRIPTION
		"Columns in the ltmTftpProfile Table"
	INDEX {
		ltmTftpProfileName
	}
	::= { ltmTftpProfileTable 1 }

LtmTftpProfileEntry ::=
	SEQUENCE {
        	ltmTftpProfileName                                        LongDisplayString,
        	ltmTftpProfileConfigSource                                INTEGER,
        	ltmTftpProfileDefaultName                                 LongDisplayString,
        	ltmTftpProfileIdleTimeout                                 Gauge,
        	ltmTftpProfileLogPublisher                                LongDisplayString,
        	ltmTftpProfileLogProfile                                  LongDisplayString
	}

ltmTftpProfileName OBJECT-TYPE
	SYNTAX LongDisplayString
	MAX-ACCESS read-only
	STATUS current
	DESCRIPTION
		"The name of a TFTP profile."
	::= { ltmTftpProfileEntry 1 }

ltmTftpProfileConfigSource OBJECT-TYPE
	SYNTAX INTEGER {
		usercfg(0),
		basecfg(1)
	}
	MAX-ACCESS read-only
	STATUS current
	DESCRIPTION
		"The state that specifies whether this is a base/pre-configured profile
		or user defined profile."
	::= { ltmTftpProfileEntry 2 }

ltmTftpProfileDefaultName OBJECT-TYPE
	SYNTAX LongDisplayString
	MAX-ACCESS read-only
	STATUS current
	DESCRIPTION
		"The name of the profile from which the specified profile derives
		its attribute default values."
	::= { ltmTftpProfileEntry 3 }

ltmTftpProfileIdleTimeout OBJECT-TYPE
	SYNTAX Gauge
	MAX-ACCESS read-only
	STATUS current
	DESCRIPTION
		"The idle timeout for TFTP connections."
	::= { ltmTftpProfileEntry 4 }

ltmTftpProfileLogPublisher OBJECT-TYPE
	SYNTAX LongDisplayString
	MAX-ACCESS read-only
	STATUS current
	DESCRIPTION
		"Specifies the name of the log publisher that logs ALG events, if any."
	::= { ltmTftpProfileEntry 5 }

ltmTftpProfileLogProfile OBJECT-TYPE
	SYNTAX LongDisplayString
	MAX-ACCESS read-only
	STATUS current
	DESCRIPTION
		"Specifies the name of the log profile that control the logging of ALG events, if any."
	::= { ltmTftpProfileEntry 6 }

--==================================================================
-- Profile_tftp_stat
--==================================================================
ltmTftpProfileStatResetStats OBJECT-TYPE
	SYNTAX INTEGER
	MAX-ACCESS read-write
	STATUS current
	DESCRIPTION
		"The action to reset resettable statistics data in ltmTftpProfileStat.
		 Setting this value to 1 will reset statistics data.
		 Note, some statistics data may not be reset including data that are incremental counters."
	::= { ltmTftpProfileStat 1 }

ltmTftpProfileStatNumber OBJECT-TYPE
	SYNTAX INTEGER
	MAX-ACCESS read-only
	STATUS current
	DESCRIPTION
		"The number of ltmTftpProfileStat entries in the table."
	::= { ltmTftpProfileStat 2 }

ltmTftpProfileStatTable OBJECT-TYPE
	SYNTAX SEQUENCE OF LtmTftpProfileStatEntry
	MAX-ACCESS not-accessible
	STATUS current
	DESCRIPTION
		"A table containing statistics information for the TFTP profile."
	::= { ltmTftpProfileStat 3 }

ltmTftpProfileStatEntry OBJECT-TYPE
	SYNTAX  LtmTftpProfileStatEntry
	MAX-ACCESS not-accessible
	STATUS current
	DESCRIPTION
		"Columns in the ltmTftpProfileStat Table"
	INDEX {
		ltmTftpProfileStatName
	}
	::= { ltmTftpProfileStatTable 1 }

LtmTftpProfileStatEntry ::=
	SEQUENCE {
        	ltmTftpProfileStatName                                    LongDisplayString,
        	ltmTftpProfileStatReadRequests                            Counter64,
        	ltmTftpProfileStatWriteRequests                           Counter64,
        	ltmTftpProfileStatDiscardedRequests                       Counter64
	}

ltmTftpProfileStatName OBJECT-TYPE
	SYNTAX LongDisplayString
	MAX-ACCESS read-only
	STATUS current
	DESCRIPTION
		"The name of the TFTP profile."
	::= { ltmTftpProfileStatEntry 1 }

ltmTftpProfileStatReadRequests OBJECT-TYPE
	SYNTAX Counter64
	MAX-ACCESS read-only
	STATUS current
	DESCRIPTION
		"The total number of read requests received."
	::= { ltmTftpProfileStatEntry 2 }

ltmTftpProfileStatWriteRequests OBJECT-TYPE
	SYNTAX Counter64
	MAX-ACCESS read-only
	STATUS current
	DESCRIPTION
		"The total number of write requests received."
	::= { ltmTftpProfileStatEntry 3 }

ltmTftpProfileStatDiscardedRequests OBJECT-TYPE
	SYNTAX Counter64
	MAX-ACCESS read-only
	STATUS current
	DESCRIPTION
		"The total number of requests that were discarded."
	::= { ltmTftpProfileStatEntry 4 }

--==================================================================
-- Profile_ipsecalg
--==================================================================
ltmIpsecalgProfileNumber OBJECT-TYPE
	SYNTAX INTEGER
	MAX-ACCESS read-only
	STATUS current
	DESCRIPTION
		"The number of ltmIpsecalgProfile entries in the table."
	::= { ltmIpsecalgProfile 1 }

ltmIpsecalgProfileTable OBJECT-TYPE
	SYNTAX SEQUENCE OF LtmIpsecalgProfileEntry
	MAX-ACCESS not-accessible
	STATUS current
	DESCRIPTION
		"A table containing information for IPsecALG profiles."
	::= { ltmIpsecalgProfile 2 }

ltmIpsecalgProfileEntry OBJECT-TYPE
	SYNTAX  LtmIpsecalgProfileEntry
	MAX-ACCESS not-accessible
	STATUS current
	DESCRIPTION
		"Columns in the ltmIpsecalgProfile Table"
	INDEX {
		ltmIpsecalgProfileName
	}
	::= { ltmIpsecalgProfileTable 1 }

LtmIpsecalgProfileEntry ::=
	SEQUENCE {
        	ltmIpsecalgProfileName                                    LongDisplayString,
        	ltmIpsecalgProfileConfigSource                            INTEGER,
        	ltmIpsecalgProfileDefaultName                             LongDisplayString,
        	ltmIpsecalgProfileIdleTimeout                             Gauge,
        	ltmIpsecalgProfilePendingIkeConnectionLimit               Gauge,
        	ltmIpsecalgProfileInitialConnectionTimeout                Gauge,
        	ltmIpsecalgProfileLogPublisher                            LongDisplayString,
        	ltmIpsecalgProfileLogProfile                              LongDisplayString
	}

ltmIpsecalgProfileName OBJECT-TYPE
	SYNTAX LongDisplayString
	MAX-ACCESS read-only
	STATUS current
	DESCRIPTION
		"The name of a IPsecALG profile."
	::= { ltmIpsecalgProfileEntry 1 }

ltmIpsecalgProfileConfigSource OBJECT-TYPE
	SYNTAX INTEGER {
		usercfg(0),
		basecfg(1)
	}
	MAX-ACCESS read-only
	STATUS current
	DESCRIPTION
		"The state that specifies whether this is a base/pre-configured profile
		or user defined profile."
	::= { ltmIpsecalgProfileEntry 2 }

ltmIpsecalgProfileDefaultName OBJECT-TYPE
	SYNTAX LongDisplayString
	MAX-ACCESS read-only
	STATUS current
	DESCRIPTION
		"The name of the profile from which the specified profile derives
		its attribute default values."
	::= { ltmIpsecalgProfileEntry 3 }

ltmIpsecalgProfileIdleTimeout OBJECT-TYPE
	SYNTAX Gauge
	MAX-ACCESS read-only
	STATUS current
	DESCRIPTION
		"The idle timeout for IPsecALG connections."
	::= { ltmIpsecalgProfileEntry 4 }

ltmIpsecalgProfilePendingIkeConnectionLimit OBJECT-TYPE
	SYNTAX Gauge
	MAX-ACCESS read-only
	STATUS current
	DESCRIPTION
		"The pending IKE connections limit per client for IPsecALG connections."
	::= { ltmIpsecalgProfileEntry 5 }

ltmIpsecalgProfileInitialConnectionTimeout OBJECT-TYPE
	SYNTAX Gauge
	MAX-ACCESS read-only
	STATUS current
	DESCRIPTION
		"The initial connection timeout for servers to respond to an IKE/IPSEC request."
	::= { ltmIpsecalgProfileEntry 6 }

ltmIpsecalgProfileLogPublisher OBJECT-TYPE
	SYNTAX LongDisplayString
	MAX-ACCESS read-only
	STATUS current
	DESCRIPTION
		"Specifies the name of the log publisher that logs ALG events, if any."
	::= { ltmIpsecalgProfileEntry 7 }

ltmIpsecalgProfileLogProfile OBJECT-TYPE
	SYNTAX LongDisplayString
	MAX-ACCESS read-only
	STATUS current
	DESCRIPTION
		"Specifies the name of the log profile that control the logging of ALG events, if any."
	::= { ltmIpsecalgProfileEntry 8 }

--==================================================================
-- Profile_http_known_methods
--==================================================================
ltmKnownMethodsNumber OBJECT-TYPE
	SYNTAX INTEGER
	MAX-ACCESS read-only
	STATUS current
	DESCRIPTION
		"The number of ltmHttpProfileKnownMethods entries in the table."
	::= { ltmHttpProfileKnownMethods 1 }

ltmKnownMethodsTable OBJECT-TYPE
	SYNTAX SEQUENCE OF LtmKnownMethodsEntry
	MAX-ACCESS not-accessible
	STATUS current
	DESCRIPTION
		"A table containing the known HTTP methods in the HTTP profiles."
	::= { ltmHttpProfileKnownMethods 2 }

ltmKnownMethodsEntry OBJECT-TYPE
	SYNTAX  LtmKnownMethodsEntry
	MAX-ACCESS not-accessible
	STATUS current
	DESCRIPTION
		"Columns in the ltmKnownMethods Table"
	INDEX {
		ltmKnownMethodsName,
		ltmKnownMethodsIndex
	}
	::= { ltmKnownMethodsTable 1 }

LtmKnownMethodsEntry ::=
	SEQUENCE {
        	ltmKnownMethodsName                                       LongDisplayString,
        	ltmKnownMethodsIndex                                      INTEGER,
        	ltmKnownMethodsStr                                        LongDisplayString
	}

ltmKnownMethodsName OBJECT-TYPE
	SYNTAX LongDisplayString
	MAX-ACCESS read-only
	STATUS current
	DESCRIPTION
		"The name of a HTTP profile."
	::= { ltmKnownMethodsEntry 1 }

ltmKnownMethodsIndex OBJECT-TYPE
	SYNTAX INTEGER(0..2147483647)
	MAX-ACCESS read-only
	STATUS current
	DESCRIPTION
		"The index of a known HTTP method for the specified HTTP profile."
	::= { ltmKnownMethodsEntry 2 }

ltmKnownMethodsStr OBJECT-TYPE
	SYNTAX LongDisplayString
	MAX-ACCESS read-only
	STATUS current
	DESCRIPTION
		"A known HTTP method in the specified profile."
	::= { ltmKnownMethodsEntry 3 }

--==================================================================
-- Profile_ipsecalg_stat
--==================================================================
ltmIpsecalgProfileStatResetStats OBJECT-TYPE
	SYNTAX INTEGER
	MAX-ACCESS read-write
	STATUS current
	DESCRIPTION
		"The action to reset resettable statistics data in ltmIpsecalgProfileStat.
		 Setting this value to 1 will reset statistics data.
		 Note, some statistics data may not be reset including data that are incremental counters."
	::= { ltmIpsecalgProfileStat 1 }

ltmIpsecalgProfileStatNumber OBJECT-TYPE
	SYNTAX INTEGER
	MAX-ACCESS read-only
	STATUS current
	DESCRIPTION
		"The number of ltmIpsecalgProfileStat entries in the table."
	::= { ltmIpsecalgProfileStat 2 }

ltmIpsecalgProfileStatTable OBJECT-TYPE
	SYNTAX SEQUENCE OF LtmIpsecalgProfileStatEntry
	MAX-ACCESS not-accessible
	STATUS current
	DESCRIPTION
		"A table containing statistics information for the IPsecALG profile."
	::= { ltmIpsecalgProfileStat 3 }

ltmIpsecalgProfileStatEntry OBJECT-TYPE
	SYNTAX  LtmIpsecalgProfileStatEntry
	MAX-ACCESS not-accessible
	STATUS current
	DESCRIPTION
		"Columns in the ltmIpsecalgProfileStat Table"
	INDEX {
		ltmIpsecalgProfileStatName
	}
	::= { ltmIpsecalgProfileStatTable 1 }

LtmIpsecalgProfileStatEntry ::=
	SEQUENCE {
        	ltmIpsecalgProfileStatName                                LongDisplayString,
        	ltmIpsecalgProfileStatIkePackets                          Counter64,
        	ltmIpsecalgProfileStatTunnelCreates                       Counter64,
        	ltmIpsecalgProfileStatTunnelTeardowns                     Counter64,
        	ltmIpsecalgProfileStatFailures                            Counter64,
        	ltmIpsecalgProfileStatPendingIkeConnectionLimitDrops      Counter64
	}

ltmIpsecalgProfileStatName OBJECT-TYPE
	SYNTAX LongDisplayString
	MAX-ACCESS read-only
	STATUS current
	DESCRIPTION
		"The name of the IPsecALG profile."
	::= { ltmIpsecalgProfileStatEntry 1 }

ltmIpsecalgProfileStatIkePackets OBJECT-TYPE
	SYNTAX Counter64
	MAX-ACCESS read-only
	STATUS current
	DESCRIPTION
		"Number of IKE packets."
	::= { ltmIpsecalgProfileStatEntry 2 }

ltmIpsecalgProfileStatTunnelCreates OBJECT-TYPE
	SYNTAX Counter64
	MAX-ACCESS read-only
	STATUS current
	DESCRIPTION
		"Number of tunnel creates."
	::= { ltmIpsecalgProfileStatEntry 3 }

ltmIpsecalgProfileStatTunnelTeardowns OBJECT-TYPE
	SYNTAX Counter64
	MAX-ACCESS read-only
	STATUS current
	DESCRIPTION
		"Number of tunnel teardowns."
	::= { ltmIpsecalgProfileStatEntry 4 }

ltmIpsecalgProfileStatFailures OBJECT-TYPE
	SYNTAX Counter64
	MAX-ACCESS read-only
	STATUS current
	DESCRIPTION
		"Number of failed connection attempts."
	::= { ltmIpsecalgProfileStatEntry 5 }

ltmIpsecalgProfileStatPendingIkeConnectionLimitDrops OBJECT-TYPE
	SYNTAX Counter64
	MAX-ACCESS read-only
	STATUS current
	DESCRIPTION
		"Number of dropped IKE connections because a client exceeded its limit of pending unacknowledged connections."
	::= { ltmIpsecalgProfileStatEntry 6 }

--==================================================================
-- Profile_http2
--==================================================================
ltmHttp2ProfileNumber OBJECT-TYPE
	SYNTAX INTEGER
	MAX-ACCESS read-only
	STATUS current
	DESCRIPTION
		"The number of ltmHttp2Profile entries in the table."
	::= { ltmHttp2Profile 1 }

ltmHttp2ProfileTable OBJECT-TYPE
	SYNTAX SEQUENCE OF LtmHttp2ProfileEntry
	MAX-ACCESS not-accessible
	STATUS current
	DESCRIPTION
		"A table containing information about the HTTP/2 profile."
	::= { ltmHttp2Profile 2 }

ltmHttp2ProfileEntry OBJECT-TYPE
	SYNTAX  LtmHttp2ProfileEntry
	MAX-ACCESS not-accessible
	STATUS current
	DESCRIPTION
		"Columns in the ltmHttp2Profile Table"
	INDEX {
		ltmHttp2ProfileName
	}
	::= { ltmHttp2ProfileTable 1 }

LtmHttp2ProfileEntry ::=
	SEQUENCE {
        	ltmHttp2ProfileName                                       LongDisplayString,
        	ltmHttp2ProfileConfigSource                               INTEGER,
        	ltmHttp2ProfileDefaultName                                LongDisplayString,
        	ltmHttp2ProfileInsertHeader                               INTEGER,
        	ltmHttp2ProfileInsertHeaderName                           LongDisplayString,
        	ltmHttp2ProfileConcurrentStreamsPerConnection             Gauge,
        	ltmHttp2ProfileConnectionIdleTimeout                      Gauge,
        	ltmHttp2ProfileReceiveWindow                              Gauge,
        	ltmHttp2ProfileFrameSize                                  Gauge,
        	ltmHttp2ProfileWriteSize                                  Gauge,
        	ltmHttp2ProfileHeaderTableSize                            Gauge,
        	ltmHttp2ProfileEnforceTlsRequirements                     INTEGER,
        	ltmHttp2ProfileIncludeContentLength                       INTEGER
	}

ltmHttp2ProfileName OBJECT-TYPE
	SYNTAX LongDisplayString
	MAX-ACCESS read-only
	STATUS current
	DESCRIPTION
		"The name of a HTTP/2 profile."
	::= { ltmHttp2ProfileEntry 1 }

ltmHttp2ProfileConfigSource OBJECT-TYPE
	SYNTAX INTEGER {
		usercfg(0),
		basecfg(1)
	}
	MAX-ACCESS read-only
	STATUS current
	DESCRIPTION
		"The state that specifies whether this is a base/pre-configured profile
		or user defined profile."
	::= { ltmHttp2ProfileEntry 2 }

ltmHttp2ProfileDefaultName OBJECT-TYPE
	SYNTAX LongDisplayString
	MAX-ACCESS read-only
	STATUS current
	DESCRIPTION
		"The name of the profile from which the specified profile derives
		its attribute default values."
	::= { ltmHttp2ProfileEntry 3 }

ltmHttp2ProfileInsertHeader OBJECT-TYPE
	SYNTAX INTEGER {
		false(0),
		true(1)
	}
	MAX-ACCESS read-only
	STATUS current
	DESCRIPTION
		"The state indicating whether or not an HTTP header that indicates the
	         use of HTTP/2 should be inserted into the request going to the back-end
	         server."
	::= { ltmHttp2ProfileEntry 4 }

ltmHttp2ProfileInsertHeaderName OBJECT-TYPE
	SYNTAX LongDisplayString
	MAX-ACCESS read-only
	STATUS current
	DESCRIPTION
		"The HTTP header inserted into the request going to the back-end server,
	         if that functionality is enabled."
	::= { ltmHttp2ProfileEntry 5 }

ltmHttp2ProfileConcurrentStreamsPerConnection OBJECT-TYPE
	SYNTAX Gauge
	MAX-ACCESS read-only
	STATUS current
	DESCRIPTION
		"The maximum amount of concurrent streams allowed per connection."
	::= { ltmHttp2ProfileEntry 6 }

ltmHttp2ProfileConnectionIdleTimeout OBJECT-TYPE
	SYNTAX Gauge
	MAX-ACCESS read-only
	STATUS current
	DESCRIPTION
		"The amount of time, in seconds, a connection is open idly before it is
	         shutdown."
	::= { ltmHttp2ProfileEntry 7 }

ltmHttp2ProfileReceiveWindow OBJECT-TYPE
	SYNTAX Gauge
	MAX-ACCESS read-only
	STATUS current
	DESCRIPTION
		"Specifies the size of the receive window in kilobytes. The receive
	         window is a mechanism to stall individual upload streams when
	         needed."
	::= { ltmHttp2ProfileEntry 8 }

ltmHttp2ProfileFrameSize OBJECT-TYPE
	SYNTAX Gauge
	MAX-ACCESS read-only
	STATUS current
	DESCRIPTION
		"Specifies the size of the data frames, in bytes, that HTTP/2 will send to
	         the client. Larger frame sizes will improve network utilization, but
	         may affect concurrency."
	::= { ltmHttp2ProfileEntry 9 }

ltmHttp2ProfileWriteSize OBJECT-TYPE
	SYNTAX Gauge
	MAX-ACCESS read-only
	STATUS current
	DESCRIPTION
		"Specifies the total size of combined data frames, in bytes, HTTP/2 will
	         send in a single write. This controls the size of the TLS records when
	         HTTP/2 is used over SSL. A large write size will cause HTTP/2 to buffer
	         more data, but will improve network utilization."
	::= { ltmHttp2ProfileEntry 10 }

ltmHttp2ProfileHeaderTableSize OBJECT-TYPE
	SYNTAX Gauge
	MAX-ACCESS read-only
	STATUS current
	DESCRIPTION
		"Specifies the total size of the header table that will be used to
	         decompress HTTP/2 requests."
	::= { ltmHttp2ProfileEntry 11 }

ltmHttp2ProfileEnforceTlsRequirements OBJECT-TYPE
	SYNTAX INTEGER {
		false(0),
		true(1)
	}
	MAX-ACCESS read-only
	STATUS current
	DESCRIPTION
		"Specifies whether the TLS connection requirements, as
	         specified in the HTTP/2 protocol specification, will be enforced."
	::= { ltmHttp2ProfileEntry 12 }

ltmHttp2ProfileIncludeContentLength OBJECT-TYPE
	SYNTAX INTEGER {
		false(0),
		true(1)
	}
	MAX-ACCESS read-only
	STATUS current
	DESCRIPTION
		"Ignored.  The Content Length header is always sent."
	::= { ltmHttp2ProfileEntry 13 }

--==================================================================
-- Profile_http2_activation_modes
--==================================================================
ltmHttp2ProfileActivationModesNumber OBJECT-TYPE
	SYNTAX INTEGER
	MAX-ACCESS read-only
	STATUS current
	DESCRIPTION
		"The number of ltmHttp2ProfileActivationModes entries in the table."
	::= { ltmHttp2ProfileActivationModes 1 }

ltmHttp2ProfileActivationModesTable OBJECT-TYPE
	SYNTAX SEQUENCE OF LtmHttp2ProfileActivationModesEntry
	MAX-ACCESS not-accessible
	STATUS current
	DESCRIPTION
		"A table containing information on the supported HTTP/2 activation
	        modes."
	::= { ltmHttp2ProfileActivationModes 2 }

ltmHttp2ProfileActivationModesEntry OBJECT-TYPE
	SYNTAX  LtmHttp2ProfileActivationModesEntry
	MAX-ACCESS not-accessible
	STATUS current
	DESCRIPTION
		"Columns in the ltmHttp2ProfileActivationModes Table"
	INDEX {
		ltmHttp2ProfileActivationModesName,
		ltmHttp2ProfileActivationModesIndex
	}
	::= { ltmHttp2ProfileActivationModesTable 1 }

LtmHttp2ProfileActivationModesEntry ::=
	SEQUENCE {
        	ltmHttp2ProfileActivationModesName                        LongDisplayString,
        	ltmHttp2ProfileActivationModesIndex                       INTEGER,
        	ltmHttp2ProfileActivationModesActivationModes             INTEGER
	}

ltmHttp2ProfileActivationModesName OBJECT-TYPE
	SYNTAX LongDisplayString
	MAX-ACCESS read-only
	STATUS current
	DESCRIPTION
		"The name of a HTTP/2 profile."
	::= { ltmHttp2ProfileActivationModesEntry 1 }

ltmHttp2ProfileActivationModesIndex OBJECT-TYPE
	SYNTAX INTEGER(0..2147483647)
	MAX-ACCESS read-only
	STATUS current
	DESCRIPTION
		"The index of the protocol versions used to determine which HTTP/2
	         versions are supported and in what order those versions should be
	         prioritized when deciding which version to use. This prioritization is
	         only used when the activation mode is set to npn."
	::= { ltmHttp2ProfileActivationModesEntry 2 }

ltmHttp2ProfileActivationModesActivationModes OBJECT-TYPE
	SYNTAX INTEGER {
		alpn(0),
		npn(1),
		always(2)
	}
	MAX-ACCESS read-only
	STATUS current
	DESCRIPTION
		"The HTTP/2 version supported.
	         alpn - indicates that HTTP/2 will be negotiated through the TLS ALPN extension
	         npn - indicates that HTTP/2 will be negotiated through the TLS NPN extension
	         always - indicates that HTTP/2 is always active"
	::= { ltmHttp2ProfileActivationModesEntry 3 }

--==================================================================
-- Profile_http2_stat
--==================================================================
ltmHttp2ProfileStatResetStats OBJECT-TYPE
	SYNTAX INTEGER
	MAX-ACCESS read-write
	STATUS current
	DESCRIPTION
		"The action to reset resettable statistics data in ltmHttp2ProfileStat.
		 Setting this value to 1 will reset statistics data.
		 Note, some statistics data may not be reset including data that are incremental counters."
	::= { ltmHttp2ProfileStat 1 }

ltmHttp2ProfileStatNumber OBJECT-TYPE
	SYNTAX INTEGER
	MAX-ACCESS read-only
	STATUS current
	DESCRIPTION
		"The number of ltmHttp2ProfileStat entries in the table."
	::= { ltmHttp2ProfileStat 2 }

ltmHttp2ProfileStatTable OBJECT-TYPE
	SYNTAX SEQUENCE OF LtmHttp2ProfileStatEntry
	MAX-ACCESS not-accessible
	STATUS current
	DESCRIPTION
		"A table containing statistics information about the HTTP/2 profile."
	::= { ltmHttp2ProfileStat 3 }

ltmHttp2ProfileStatEntry OBJECT-TYPE
	SYNTAX  LtmHttp2ProfileStatEntry
	MAX-ACCESS not-accessible
	STATUS current
	DESCRIPTION
		"Columns in the ltmHttp2ProfileStat Table"
	INDEX {
		ltmHttp2ProfileStatName
	}
	::= { ltmHttp2ProfileStatTable 1 }

LtmHttp2ProfileStatEntry ::=
	SEQUENCE {
        	ltmHttp2ProfileStatName                                   LongDisplayString,
        	ltmHttp2ProfileStatConnectionsAccepted                    Counter64,
        	ltmHttp2ProfileStatConnectionsCurrent                     Counter64,
        	ltmHttp2ProfileStatConnectionsMax                         Counter64,
        	ltmHttp2ProfileStatContinuationFramesReceived             Counter64,
        	ltmHttp2ProfileStatContinuationFramesSent                 Counter64,
        	ltmHttp2ProfileStatDataFramesReceived                     Counter64,
        	ltmHttp2ProfileStatDataFramesSent                         Counter64,
        	ltmHttp2ProfileStatFlowsCreated                           Counter64,
        	ltmHttp2ProfileStatFlowsCurrent                           Counter64,
        	ltmHttp2ProfileStatFlowsMax                               Counter64,
        	ltmHttp2ProfileStatGoawayFramesReceived                   Counter64,
        	ltmHttp2ProfileStatGoawayFramesSent                       Counter64,
        	ltmHttp2ProfileStatHeadersFramesReceived                  Counter64,
        	ltmHttp2ProfileStatHeadersFramesSent                      Counter64,
        	ltmHttp2ProfileStatHttp2RequestBytes                      Counter64,
        	ltmHttp2ProfileStatHttp2RequestFrames                     Counter64,
        	ltmHttp2ProfileStatHttp2ResponseBytes                     Counter64,
        	ltmHttp2ProfileStatHttp2ResponseFrames                    Counter64,
        	ltmHttp2ProfileStatHttpRequestBytes                       Counter64,
        	ltmHttp2ProfileStatHttpResponseBytes                      Counter64,
        	ltmHttp2ProfileStatPingFramesReceived                     Counter64,
        	ltmHttp2ProfileStatPingFramesSent                         Counter64,
        	ltmHttp2ProfileStatPriorityFramesReceived                 Counter64,
        	ltmHttp2ProfileStatPriorityFramesSent                     Counter64,
        	ltmHttp2ProfileStatPushPromiseFramesReceived              Counter64,
        	ltmHttp2ProfileStatPushPromiseFramesSent                  Counter64,
        	ltmHttp2ProfileStatRstStreamFramesReceived                Counter64,
        	ltmHttp2ProfileStatRstStreamFramesSent                    Counter64,
        	ltmHttp2ProfileStatSettingsFramesReceived                 Counter64,
        	ltmHttp2ProfileStatSettingsFramesSent                     Counter64,
        	ltmHttp2ProfileStatStreamsCreated                         Counter64,
        	ltmHttp2ProfileStatStreamsCurrent                         Counter64,
        	ltmHttp2ProfileStatStreamsMax                             Counter64,
        	ltmHttp2ProfileStatWindowUpdateFramesReceived             Counter64,
        	ltmHttp2ProfileStatWindowUpdateFramesSent                 Counter64
	}

ltmHttp2ProfileStatName OBJECT-TYPE
	SYNTAX LongDisplayString
	MAX-ACCESS read-only
	STATUS current
	DESCRIPTION
		"The name of the HTTP/2 profile."
	::= { ltmHttp2ProfileStatEntry 1 }

ltmHttp2ProfileStatConnectionsAccepted OBJECT-TYPE
	SYNTAX Counter64
	MAX-ACCESS read-only
	STATUS current
	DESCRIPTION
		"The total number of accepted connections."
	::= { ltmHttp2ProfileStatEntry 2 }

ltmHttp2ProfileStatConnectionsCurrent OBJECT-TYPE
	SYNTAX Counter64
	MAX-ACCESS read-only
	STATUS current
	DESCRIPTION
		"The total number of connections currently active."
	::= { ltmHttp2ProfileStatEntry 3 }

ltmHttp2ProfileStatConnectionsMax OBJECT-TYPE
	SYNTAX Counter64
	MAX-ACCESS read-only
	STATUS current
	DESCRIPTION
		"The maximum number of connections open simultaneously."
	::= { ltmHttp2ProfileStatEntry 4 }

ltmHttp2ProfileStatContinuationFramesReceived OBJECT-TYPE
	SYNTAX Counter64
	MAX-ACCESS read-only
	STATUS current
	DESCRIPTION
		"The total number of CONTINUATION frames received."
	::= { ltmHttp2ProfileStatEntry 5 }

ltmHttp2ProfileStatContinuationFramesSent OBJECT-TYPE
	SYNTAX Counter64
	MAX-ACCESS read-only
	STATUS current
	DESCRIPTION
		"The total number of CONTINUATION frames sent."
	::= { ltmHttp2ProfileStatEntry 6 }

ltmHttp2ProfileStatDataFramesReceived OBJECT-TYPE
	SYNTAX Counter64
	MAX-ACCESS read-only
	STATUS current
	DESCRIPTION
		"The total number of DATA frames received."
	::= { ltmHttp2ProfileStatEntry 7 }

ltmHttp2ProfileStatDataFramesSent OBJECT-TYPE
	SYNTAX Counter64
	MAX-ACCESS read-only
	STATUS current
	DESCRIPTION
		"The total number of DATA frames sent."
	::= { ltmHttp2ProfileStatEntry 8 }

ltmHttp2ProfileStatFlowsCreated OBJECT-TYPE
	SYNTAX Counter64
	MAX-ACCESS read-only
	STATUS current
	DESCRIPTION
		"The total number of flows created."
	::= { ltmHttp2ProfileStatEntry 9 }

ltmHttp2ProfileStatFlowsCurrent OBJECT-TYPE
	SYNTAX Counter64
	MAX-ACCESS read-only
	STATUS current
	DESCRIPTION
		"The total number of flows currently active."
	::= { ltmHttp2ProfileStatEntry 10 }

ltmHttp2ProfileStatFlowsMax OBJECT-TYPE
	SYNTAX Counter64
	MAX-ACCESS read-only
	STATUS current
	DESCRIPTION
		"The maximum number of flows open simultaneously."
	::= { ltmHttp2ProfileStatEntry 11 }

ltmHttp2ProfileStatGoawayFramesReceived OBJECT-TYPE
	SYNTAX Counter64
	MAX-ACCESS read-only
	STATUS current
	DESCRIPTION
		"The total number of GOAWAY frames received."
	::= { ltmHttp2ProfileStatEntry 12 }

ltmHttp2ProfileStatGoawayFramesSent OBJECT-TYPE
	SYNTAX Counter64
	MAX-ACCESS read-only
	STATUS current
	DESCRIPTION
		"The total number of GOAWAY frames sent."
	::= { ltmHttp2ProfileStatEntry 13 }

ltmHttp2ProfileStatHeadersFramesReceived OBJECT-TYPE
	SYNTAX Counter64
	MAX-ACCESS read-only
	STATUS current
	DESCRIPTION
		"The total number of HEADERS frames received."
	::= { ltmHttp2ProfileStatEntry 14 }

ltmHttp2ProfileStatHeadersFramesSent OBJECT-TYPE
	SYNTAX Counter64
	MAX-ACCESS read-only
	STATUS current
	DESCRIPTION
		"The total number of HEADERS frames sent."
	::= { ltmHttp2ProfileStatEntry 15 }

ltmHttp2ProfileStatHttp2RequestBytes OBJECT-TYPE
	SYNTAX Counter64
	MAX-ACCESS read-only
	STATUS current
	DESCRIPTION
		"The total number of HTTP/2 request bytes."
	::= { ltmHttp2ProfileStatEntry 16 }

ltmHttp2ProfileStatHttp2RequestFrames OBJECT-TYPE
	SYNTAX Counter64
	MAX-ACCESS read-only
	STATUS current
	DESCRIPTION
		"The total number of HTTP/2 request frames."
	::= { ltmHttp2ProfileStatEntry 17 }

ltmHttp2ProfileStatHttp2ResponseBytes OBJECT-TYPE
	SYNTAX Counter64
	MAX-ACCESS read-only
	STATUS current
	DESCRIPTION
		"The total number of HTTP/2 response bytes."
	::= { ltmHttp2ProfileStatEntry 18 }

ltmHttp2ProfileStatHttp2ResponseFrames OBJECT-TYPE
	SYNTAX Counter64
	MAX-ACCESS read-only
	STATUS current
	DESCRIPTION
		"The total number of HTTP/2 response frames."
	::= { ltmHttp2ProfileStatEntry 19 }

ltmHttp2ProfileStatHttpRequestBytes OBJECT-TYPE
	SYNTAX Counter64
	MAX-ACCESS read-only
	STATUS current
	DESCRIPTION
		"The total number of HTTP request bytes."
	::= { ltmHttp2ProfileStatEntry 20 }

ltmHttp2ProfileStatHttpResponseBytes OBJECT-TYPE
	SYNTAX Counter64
	MAX-ACCESS read-only
	STATUS current
	DESCRIPTION
		"The total number of HTTP response bytes."
	::= { ltmHttp2ProfileStatEntry 21 }

ltmHttp2ProfileStatPingFramesReceived OBJECT-TYPE
	SYNTAX Counter64
	MAX-ACCESS read-only
	STATUS current
	DESCRIPTION
		"The total number of PING frames received."
	::= { ltmHttp2ProfileStatEntry 22 }

ltmHttp2ProfileStatPingFramesSent OBJECT-TYPE
	SYNTAX Counter64
	MAX-ACCESS read-only
	STATUS current
	DESCRIPTION
		"The total number of PING frames sent."
	::= { ltmHttp2ProfileStatEntry 23 }

ltmHttp2ProfileStatPriorityFramesReceived OBJECT-TYPE
	SYNTAX Counter64
	MAX-ACCESS read-only
	STATUS current
	DESCRIPTION
		"The total number of PRIORITY frames received."
	::= { ltmHttp2ProfileStatEntry 24 }

ltmHttp2ProfileStatPriorityFramesSent OBJECT-TYPE
	SYNTAX Counter64
	MAX-ACCESS read-only
	STATUS current
	DESCRIPTION
		"The total number of PRIORITY frames sent."
	::= { ltmHttp2ProfileStatEntry 25 }

ltmHttp2ProfileStatPushPromiseFramesReceived OBJECT-TYPE
	SYNTAX Counter64
	MAX-ACCESS read-only
	STATUS current
	DESCRIPTION
		"The total number of PUSH_PROMISE frames received."
	::= { ltmHttp2ProfileStatEntry 26 }

ltmHttp2ProfileStatPushPromiseFramesSent OBJECT-TYPE
	SYNTAX Counter64
	MAX-ACCESS read-only
	STATUS current
	DESCRIPTION
		"The total number of PUSH_PROMISE frames sent."
	::= { ltmHttp2ProfileStatEntry 27 }

ltmHttp2ProfileStatRstStreamFramesReceived OBJECT-TYPE
	SYNTAX Counter64
	MAX-ACCESS read-only
	STATUS current
	DESCRIPTION
		"The total number of RST_STREAM frames received."
	::= { ltmHttp2ProfileStatEntry 28 }

ltmHttp2ProfileStatRstStreamFramesSent OBJECT-TYPE
	SYNTAX Counter64
	MAX-ACCESS read-only
	STATUS current
	DESCRIPTION
		"The total number of RST_STREAM frames sent."
	::= { ltmHttp2ProfileStatEntry 29 }

ltmHttp2ProfileStatSettingsFramesReceived OBJECT-TYPE
	SYNTAX Counter64
	MAX-ACCESS read-only
	STATUS current
	DESCRIPTION
		"The total number of SETTINGS frames received."
	::= { ltmHttp2ProfileStatEntry 30 }

ltmHttp2ProfileStatSettingsFramesSent OBJECT-TYPE
	SYNTAX Counter64
	MAX-ACCESS read-only
	STATUS current
	DESCRIPTION
		"The total number of SETTINGS frames sent."
	::= { ltmHttp2ProfileStatEntry 31 }

ltmHttp2ProfileStatStreamsCreated OBJECT-TYPE
	SYNTAX Counter64
	MAX-ACCESS read-only
	STATUS current
	DESCRIPTION
		"The total number of HTTP/2 streams created."
	::= { ltmHttp2ProfileStatEntry 32 }

ltmHttp2ProfileStatStreamsCurrent OBJECT-TYPE
	SYNTAX Counter64
	MAX-ACCESS read-only
	STATUS current
	DESCRIPTION
		"The total number of HTTP/2 streams currently active."
	::= { ltmHttp2ProfileStatEntry 33 }

ltmHttp2ProfileStatStreamsMax OBJECT-TYPE
	SYNTAX Counter64
	MAX-ACCESS read-only
	STATUS current
	DESCRIPTION
		"The maximum number of HTTP/2 streams open simultaneously."
	::= { ltmHttp2ProfileStatEntry 34 }

ltmHttp2ProfileStatWindowUpdateFramesReceived OBJECT-TYPE
	SYNTAX Counter64
	MAX-ACCESS read-only
	STATUS current
	DESCRIPTION
		"The total number of WINDOW_UPDATE frames received."
	::= { ltmHttp2ProfileStatEntry 35 }

ltmHttp2ProfileStatWindowUpdateFramesSent OBJECT-TYPE
	SYNTAX Counter64
	MAX-ACCESS read-only
	STATUS current
	DESCRIPTION
		"The total number of WINDOW_UPDATE frames sent."
	::= { ltmHttp2ProfileStatEntry 36 }

--==================================================================
-- Lsn_pool_failure_stat
--==================================================================
ltmLsnPoolFailureStatResetStats OBJECT-TYPE
	SYNTAX INTEGER
	MAX-ACCESS read-write
	STATUS current
	DESCRIPTION
		"The action to reset resettable statistics data in ltmLsnPoolFailureStat.
		 Setting this value to 1 will reset statistics data.
		 Note, some statistics data may not be reset including data that are incremental counters."
	::= { ltmLsnPoolFailureStat 1 }

ltmLsnPoolFailureStatNumber OBJECT-TYPE
	SYNTAX INTEGER
	MAX-ACCESS read-only
	STATUS current
	DESCRIPTION
		"The number of ltmLsnPoolFailureStat entries in the table."
	::= { ltmLsnPoolFailureStat 2 }

ltmLsnPoolFailureStatTable OBJECT-TYPE
	SYNTAX SEQUENCE OF LtmLsnPoolFailureStatEntry
	MAX-ACCESS not-accessible
	STATUS current
	DESCRIPTION
		"A table containing statistic information of LSN pool failures."
	::= { ltmLsnPoolFailureStat 3 }

ltmLsnPoolFailureStatEntry OBJECT-TYPE
	SYNTAX  LtmLsnPoolFailureStatEntry
	MAX-ACCESS not-accessible
	STATUS current
	DESCRIPTION
		"Columns in the ltmLsnPoolFailureStat Table"
	INDEX {
		ltmLsnPoolFailureStatName,
		ltmLsnPoolFailureStatFailureCause
	}
	::= { ltmLsnPoolFailureStatTable 1 }

LtmLsnPoolFailureStatEntry ::=
	SEQUENCE {
        	ltmLsnPoolFailureStatName                                 LongDisplayString,
        	ltmLsnPoolFailureStatFailureCause                         LongDisplayString,
        	ltmLsnPoolFailureStatFailureCount                         Counter64
	}

ltmLsnPoolFailureStatName OBJECT-TYPE
	SYNTAX LongDisplayString
	MAX-ACCESS read-only
	STATUS current
	DESCRIPTION
		"The name of a LSN Pool."
	::= { ltmLsnPoolFailureStatEntry 1 }

ltmLsnPoolFailureStatFailureCause OBJECT-TYPE
	SYNTAX LongDisplayString
	MAX-ACCESS read-only
	STATUS current
	DESCRIPTION
		"The name of a LSN Pool failure cause."
	::= { ltmLsnPoolFailureStatEntry 2 }

ltmLsnPoolFailureStatFailureCount OBJECT-TYPE
	SYNTAX Counter64
	MAX-ACCESS read-only
	STATUS current
	DESCRIPTION
		"The value of a LSN Pool failure cause."
	::= { ltmLsnPoolFailureStatEntry 3 }

--==================================================================
-- Profile_websocket
--==================================================================
ltmWebsocketProfileNumber OBJECT-TYPE
	SYNTAX INTEGER
	MAX-ACCESS read-only
	STATUS current
	DESCRIPTION
		"The number of ltmWebsocketProfile entries in the table."
	::= { ltmWebsocketProfile 1 }

ltmWebsocketProfileTable OBJECT-TYPE
	SYNTAX SEQUENCE OF LtmWebsocketProfileEntry
	MAX-ACCESS not-accessible
	STATUS current
	DESCRIPTION
		"A table containing information about the WebSocket profile."
	::= { ltmWebsocketProfile 2 }

ltmWebsocketProfileEntry OBJECT-TYPE
	SYNTAX  LtmWebsocketProfileEntry
	MAX-ACCESS not-accessible
	STATUS current
	DESCRIPTION
		"Columns in the ltmWebsocketProfile Table"
	INDEX {
		ltmWebsocketProfileName
	}
	::= { ltmWebsocketProfileTable 1 }

LtmWebsocketProfileEntry ::=
	SEQUENCE {
        	ltmWebsocketProfileName                                   LongDisplayString,
        	ltmWebsocketProfileConfigSource                           INTEGER,
        	ltmWebsocketProfileDefaultName                            LongDisplayString,
        	ltmWebsocketProfileMasking                                INTEGER
	}

ltmWebsocketProfileName OBJECT-TYPE
	SYNTAX LongDisplayString
	MAX-ACCESS read-only
	STATUS current
	DESCRIPTION
		"The name of a WebSocket profile."
	::= { ltmWebsocketProfileEntry 1 }

ltmWebsocketProfileConfigSource OBJECT-TYPE
	SYNTAX INTEGER {
		usercfg(0),
		basecfg(1)
	}
	MAX-ACCESS read-only
	STATUS current
	DESCRIPTION
		"The state that specifies whether this is a base/pre-configured profile
		or user defined profile."
	::= { ltmWebsocketProfileEntry 2 }

ltmWebsocketProfileDefaultName OBJECT-TYPE
	SYNTAX LongDisplayString
	MAX-ACCESS read-only
	STATUS current
	DESCRIPTION
		"The name of the profile from which the specified profile derives
		its attribute default values."
	::= { ltmWebsocketProfileEntry 3 }

ltmWebsocketProfileMasking OBJECT-TYPE
	SYNTAX INTEGER {
		unmask(0),
		remask(1),
		preserve(2)
	}
	MAX-ACCESS read-only
	STATUS current
	DESCRIPTION
		"The masking operation applied to WebSocket frames.
	         unmask - WebSocket feature unmasks the frame and provides cleartext data
	                    to other features. The frames are masked again before sending
	                    the frames over the client or server.
	         remask - WebSocket feature unmasks the frame and provides cleartext data
	                    to other features. The frames are masked using configured mask again
	                    before sending the frames over the client or server.
	         preserve - WebSocket feature does not perform any masking operation on the frames."
	::= { ltmWebsocketProfileEntry 4 }

--==================================================================
-- Profile_websocket_stat
--==================================================================
ltmWebsocketProfileStatResetStats OBJECT-TYPE
	SYNTAX INTEGER
	MAX-ACCESS read-write
	STATUS current
	DESCRIPTION
		"The action to reset resettable statistics data in ltmWebsocketProfileStat.
		 Setting this value to 1 will reset statistics data.
		 Note, some statistics data may not be reset including data that are incremental counters."
	::= { ltmWebsocketProfileStat 1 }

ltmWebsocketProfileStatNumber OBJECT-TYPE
	SYNTAX INTEGER
	MAX-ACCESS read-only
	STATUS current
	DESCRIPTION
		"The number of ltmWebsocketProfileStat entries in the table."
	::= { ltmWebsocketProfileStat 2 }

ltmWebsocketProfileStatTable OBJECT-TYPE
	SYNTAX SEQUENCE OF LtmWebsocketProfileStatEntry
	MAX-ACCESS not-accessible
	STATUS current
	DESCRIPTION
		"A table containing statistics information about the WebSocket profile."
	::= { ltmWebsocketProfileStat 3 }

ltmWebsocketProfileStatEntry OBJECT-TYPE
	SYNTAX  LtmWebsocketProfileStatEntry
	MAX-ACCESS not-accessible
	STATUS current
	DESCRIPTION
		"Columns in the ltmWebsocketProfileStat Table"
	INDEX {
		ltmWebsocketProfileStatName
	}
	::= { ltmWebsocketProfileStatTable 1 }

LtmWebsocketProfileStatEntry ::=
	SEQUENCE {
        	ltmWebsocketProfileStatName                               LongDisplayString,
        	ltmWebsocketProfileStatConnectionsAccepted                Counter64,
        	ltmWebsocketProfileStatConnectionsCurrent                 Counter64,
        	ltmWebsocketProfileStatConnectionsMax                     Counter64,
        	ltmWebsocketProfileStatContFramesClientRecv               Counter64,
        	ltmWebsocketProfileStatContFramesServerRecv               Counter64,
        	ltmWebsocketProfileStatTextFramesClientRecv               Counter64,
        	ltmWebsocketProfileStatTextFramesServerRecv               Counter64,
        	ltmWebsocketProfileStatBinaryFramesClientRecv             Counter64,
        	ltmWebsocketProfileStatBinaryFramesServerRecv             Counter64,
        	ltmWebsocketProfileStatCloseFramesClientRecv              Counter64,
        	ltmWebsocketProfileStatCloseFramesServerRecv              Counter64,
        	ltmWebsocketProfileStatPingFramesClientRecv               Counter64,
        	ltmWebsocketProfileStatPingFramesServerRecv               Counter64,
        	ltmWebsocketProfileStatPongFramesClientRecv               Counter64,
        	ltmWebsocketProfileStatPongFramesServerRecv               Counter64,
        	ltmWebsocketProfileStatCloseRsnNormalClientRecv           Counter64,
        	ltmWebsocketProfileStatCloseRsnNormalServerRecv           Counter64,
        	ltmWebsocketProfileStatCloseRsnEpGoawayClientRecv         Counter64,
        	ltmWebsocketProfileStatCloseRsnEpGoawayServerRecv         Counter64,
        	ltmWebsocketProfileStatCloseRsnProtErrClientRecv          Counter64,
        	ltmWebsocketProfileStatCloseRsnProtErrServerRecv          Counter64,
        	ltmWebsocketProfileStatCloseRsnProcErrClientRecv          Counter64,
        	ltmWebsocketProfileStatCloseRsnProcErrServerRecv          Counter64,
        	ltmWebsocketProfileStatCloseRsnExtFailClientRecv          Counter64,
        	ltmWebsocketProfileStatCloseRsnExtFailServerRecv          Counter64,
        	ltmWebsocketProfileStatCloseRsnOtherClientRecv            Counter64,
        	ltmWebsocketProfileStatCloseRsnOtherServerRecv            Counter64
	}

ltmWebsocketProfileStatName OBJECT-TYPE
	SYNTAX LongDisplayString
	MAX-ACCESS read-only
	STATUS current
	DESCRIPTION
		"The name of the WebSocket profile."
	::= { ltmWebsocketProfileStatEntry 1 }

ltmWebsocketProfileStatConnectionsAccepted OBJECT-TYPE
	SYNTAX Counter64
	MAX-ACCESS read-only
	STATUS current
	DESCRIPTION
		"The total number of accepted connections."
	::= { ltmWebsocketProfileStatEntry 2 }

ltmWebsocketProfileStatConnectionsCurrent OBJECT-TYPE
	SYNTAX Counter64
	MAX-ACCESS read-only
	STATUS current
	DESCRIPTION
		"The total number of connections currently active."
	::= { ltmWebsocketProfileStatEntry 3 }

ltmWebsocketProfileStatConnectionsMax OBJECT-TYPE
	SYNTAX Counter64
	MAX-ACCESS read-only
	STATUS current
	DESCRIPTION
		"The maximum number of connections open simultaneously."
	::= { ltmWebsocketProfileStatEntry 4 }

ltmWebsocketProfileStatContFramesClientRecv OBJECT-TYPE
	SYNTAX Counter64
	MAX-ACCESS read-only
	STATUS current
	DESCRIPTION
		"The total number of CONT frames received from client."
	::= { ltmWebsocketProfileStatEntry 5 }

ltmWebsocketProfileStatContFramesServerRecv OBJECT-TYPE
	SYNTAX Counter64
	MAX-ACCESS read-only
	STATUS current
	DESCRIPTION
		"The total number of CONT frames received from server."
	::= { ltmWebsocketProfileStatEntry 6 }

ltmWebsocketProfileStatTextFramesClientRecv OBJECT-TYPE
	SYNTAX Counter64
	MAX-ACCESS read-only
	STATUS current
	DESCRIPTION
		"The total number of Text frames received from client."
	::= { ltmWebsocketProfileStatEntry 7 }

ltmWebsocketProfileStatTextFramesServerRecv OBJECT-TYPE
	SYNTAX Counter64
	MAX-ACCESS read-only
	STATUS current
	DESCRIPTION
		"The total number of Text frames received from server."
	::= { ltmWebsocketProfileStatEntry 8 }

ltmWebsocketProfileStatBinaryFramesClientRecv OBJECT-TYPE
	SYNTAX Counter64
	MAX-ACCESS read-only
	STATUS current
	DESCRIPTION
		"The total number of Binary frames received from client."
	::= { ltmWebsocketProfileStatEntry 9 }

ltmWebsocketProfileStatBinaryFramesServerRecv OBJECT-TYPE
	SYNTAX Counter64
	MAX-ACCESS read-only
	STATUS current
	DESCRIPTION
		"The total number of Binary frames received from server."
	::= { ltmWebsocketProfileStatEntry 10 }

ltmWebsocketProfileStatCloseFramesClientRecv OBJECT-TYPE
	SYNTAX Counter64
	MAX-ACCESS read-only
	STATUS current
	DESCRIPTION
		"The total number of Close frames received from client."
	::= { ltmWebsocketProfileStatEntry 11 }

ltmWebsocketProfileStatCloseFramesServerRecv OBJECT-TYPE
	SYNTAX Counter64
	MAX-ACCESS read-only
	STATUS current
	DESCRIPTION
		"The total number of Close frames received from server."
	::= { ltmWebsocketProfileStatEntry 12 }

ltmWebsocketProfileStatPingFramesClientRecv OBJECT-TYPE
	SYNTAX Counter64
	MAX-ACCESS read-only
	STATUS current
	DESCRIPTION
		"The total number of Ping frames received from client."
	::= { ltmWebsocketProfileStatEntry 13 }

ltmWebsocketProfileStatPingFramesServerRecv OBJECT-TYPE
	SYNTAX Counter64
	MAX-ACCESS read-only
	STATUS current
	DESCRIPTION
		"The total number of Ping frames received from server."
	::= { ltmWebsocketProfileStatEntry 14 }

ltmWebsocketProfileStatPongFramesClientRecv OBJECT-TYPE
	SYNTAX Counter64
	MAX-ACCESS read-only
	STATUS current
	DESCRIPTION
		"The total number of Pong frames received from client."
	::= { ltmWebsocketProfileStatEntry 15 }

ltmWebsocketProfileStatPongFramesServerRecv OBJECT-TYPE
	SYNTAX Counter64
	MAX-ACCESS read-only
	STATUS current
	DESCRIPTION
		"The total number of Pong frames received from server."
	::= { ltmWebsocketProfileStatEntry 16 }

ltmWebsocketProfileStatCloseRsnNormalClientRecv OBJECT-TYPE
	SYNTAX Counter64
	MAX-ACCESS read-only
	STATUS current
	DESCRIPTION
		"The total number of Close frames with reason Normal received from client."
	::= { ltmWebsocketProfileStatEntry 17 }

ltmWebsocketProfileStatCloseRsnNormalServerRecv OBJECT-TYPE
	SYNTAX Counter64
	MAX-ACCESS read-only
	STATUS current
	DESCRIPTION
		"The total number of Close frames with reason Normal received from server."
	::= { ltmWebsocketProfileStatEntry 18 }

ltmWebsocketProfileStatCloseRsnEpGoawayClientRecv OBJECT-TYPE
	SYNTAX Counter64
	MAX-ACCESS read-only
	STATUS current
	DESCRIPTION
		"The total number of Close frames with reason Endpoint Going Away received from client."
	::= { ltmWebsocketProfileStatEntry 19 }

ltmWebsocketProfileStatCloseRsnEpGoawayServerRecv OBJECT-TYPE
	SYNTAX Counter64
	MAX-ACCESS read-only
	STATUS current
	DESCRIPTION
		"The total number of Close frames with reason Endpoint Going Away received from server."
	::= { ltmWebsocketProfileStatEntry 20 }

ltmWebsocketProfileStatCloseRsnProtErrClientRecv OBJECT-TYPE
	SYNTAX Counter64
	MAX-ACCESS read-only
	STATUS current
	DESCRIPTION
		"The total number of Close frames with reason Protocol Error received from client."
	::= { ltmWebsocketProfileStatEntry 21 }

ltmWebsocketProfileStatCloseRsnProtErrServerRecv OBJECT-TYPE
	SYNTAX Counter64
	MAX-ACCESS read-only
	STATUS current
	DESCRIPTION
		"The total number of Close frames with reason Protocol Error received from server."
	::= { ltmWebsocketProfileStatEntry 22 }

ltmWebsocketProfileStatCloseRsnProcErrClientRecv OBJECT-TYPE
	SYNTAX Counter64
	MAX-ACCESS read-only
	STATUS current
	DESCRIPTION
		"The total number of Close frames with reason Processing Error received from client."
	::= { ltmWebsocketProfileStatEntry 23 }

ltmWebsocketProfileStatCloseRsnProcErrServerRecv OBJECT-TYPE
	SYNTAX Counter64
	MAX-ACCESS read-only
	STATUS current
	DESCRIPTION
		"The total number of Close frames with reason Processing Error received from server."
	::= { ltmWebsocketProfileStatEntry 24 }

ltmWebsocketProfileStatCloseRsnExtFailClientRecv OBJECT-TYPE
	SYNTAX Counter64
	MAX-ACCESS read-only
	STATUS current
	DESCRIPTION
		"The total number of Close frames with reason Extension Negotiation Fail received from client."
	::= { ltmWebsocketProfileStatEntry 25 }

ltmWebsocketProfileStatCloseRsnExtFailServerRecv OBJECT-TYPE
	SYNTAX Counter64
	MAX-ACCESS read-only
	STATUS current
	DESCRIPTION
		"The total number of Close frames with reason Extension Negotiation Fail received from server."
	::= { ltmWebsocketProfileStatEntry 26 }

ltmWebsocketProfileStatCloseRsnOtherClientRecv OBJECT-TYPE
	SYNTAX Counter64
	MAX-ACCESS read-only
	STATUS current
	DESCRIPTION
		"The total number of Close frames with reason Other received from client."
	::= { ltmWebsocketProfileStatEntry 27 }

ltmWebsocketProfileStatCloseRsnOtherServerRecv OBJECT-TYPE
	SYNTAX Counter64
	MAX-ACCESS read-only
	STATUS current
	DESCRIPTION
		"The total number of Close frames with reason Other received from server."
	::= { ltmWebsocketProfileStatEntry 28 }

--==================================================================
-- Profile_tcpanalytics
--==================================================================
ltmTcpanalyticsProfileNumber OBJECT-TYPE
	SYNTAX INTEGER
	MAX-ACCESS read-only
	STATUS current
	DESCRIPTION
		"The number of ltmTcpanalyticsProfile entries in the table."
	::= { ltmTcpanalyticsProfile 1 }

ltmTcpanalyticsProfileTable OBJECT-TYPE
	SYNTAX SEQUENCE OF LtmTcpanalyticsProfileEntry
	MAX-ACCESS not-accessible
	STATUS current
	DESCRIPTION
		"A table containing configuration of TCP Analytics."
	::= { ltmTcpanalyticsProfile 2 }

ltmTcpanalyticsProfileEntry OBJECT-TYPE
	SYNTAX  LtmTcpanalyticsProfileEntry
	MAX-ACCESS not-accessible
	STATUS current
	DESCRIPTION
		"Columns in the ltmTcpanalyticsProfile Table"
	INDEX {
		ltmTcpanalyticsProfileName
	}
	::= { ltmTcpanalyticsProfileTable 1 }

LtmTcpanalyticsProfileEntry ::=
	SEQUENCE {
        	ltmTcpanalyticsProfileName                                LongDisplayString,
        	ltmTcpanalyticsProfileConfigSource                        INTEGER,
        	ltmTcpanalyticsProfileDefaultName                         LongDisplayString,
        	ltmTcpanalyticsProfileCollectedByClientSide               INTEGER,
        	ltmTcpanalyticsProfileCollectedByServerSide               INTEGER,
        	ltmTcpanalyticsProfileCollectCity                         INTEGER,
        	ltmTcpanalyticsProfileCollectContinent                    INTEGER,
        	ltmTcpanalyticsProfileCollectCountry                      INTEGER,
        	ltmTcpanalyticsProfileCollectNexthop                      INTEGER,
        	ltmTcpanalyticsProfileCollectPostCode                     INTEGER,
        	ltmTcpanalyticsProfileCollectRegion                       INTEGER,
        	ltmTcpanalyticsProfileCollectRemoteHostIp                 INTEGER,
        	ltmTcpanalyticsProfileCollectRemoteHostSubnet             INTEGER,
        	ltmTcpanalyticsProfileCollectedStatsInternalLogging       INTEGER,
        	ltmTcpanalyticsProfileCollectedStatsExternalLogging       INTEGER,
        	ltmTcpanalyticsProfileExternalLoggingPublisher            LongDisplayString
	}

ltmTcpanalyticsProfileName OBJECT-TYPE
	SYNTAX LongDisplayString
	MAX-ACCESS read-only
	STATUS current
	DESCRIPTION
		"The name of a TCP analytics profile."
	::= { ltmTcpanalyticsProfileEntry 1 }

ltmTcpanalyticsProfileConfigSource OBJECT-TYPE
	SYNTAX INTEGER {
		usercfg(0),
		basecfg(1)
	}
	MAX-ACCESS read-only
	STATUS current
	DESCRIPTION
		"The state that specifies whether this is a base/pre-configured
	        profile or user defined profile."
	::= { ltmTcpanalyticsProfileEntry 2 }

ltmTcpanalyticsProfileDefaultName OBJECT-TYPE
	SYNTAX LongDisplayString
	MAX-ACCESS read-only
	STATUS current
	DESCRIPTION
		"The name of the profile from which the specified profile derives
		its attribute default values."
	::= { ltmTcpanalyticsProfileEntry 3 }

ltmTcpanalyticsProfileCollectedByClientSide OBJECT-TYPE
	SYNTAX INTEGER {
		false(0),
		true(1)
	}
	MAX-ACCESS read-only
	STATUS current
	DESCRIPTION
		"If true, client side connections collect TCP analytics data unless
	        directed otherwise by iRule. If false, client side connections only
	        collect data if directed by iRule."
	::= { ltmTcpanalyticsProfileEntry 4 }

ltmTcpanalyticsProfileCollectedByServerSide OBJECT-TYPE
	SYNTAX INTEGER {
		false(0),
		true(1)
	}
	MAX-ACCESS read-only
	STATUS current
	DESCRIPTION
		"If true, server side connections collect TCP analytics data unless
	        directed otherwise by iRule. If false, server side connections only
	        collect data if directed by iRule."
	::= { ltmTcpanalyticsProfileEntry 5 }

ltmTcpanalyticsProfileCollectCity OBJECT-TYPE
	SYNTAX INTEGER {
		false(0),
		true(1)
	}
	MAX-ACCESS read-only
	STATUS current
	DESCRIPTION
		"If true, AVR stores the city (from the GeoIP database) for the
	        remote IP address of the connection with TCP statistics. See
	        SOL11176 on support.f5.com for more on GeoIP."
	::= { ltmTcpanalyticsProfileEntry 6 }

ltmTcpanalyticsProfileCollectContinent OBJECT-TYPE
	SYNTAX INTEGER {
		false(0),
		true(1)
	}
	MAX-ACCESS read-only
	STATUS current
	DESCRIPTION
		"If true, AVR stores the continent (from the GeoIP database) for the
	        remote IP address of the connection with TCP statistics. See
	        SOL11176 on support.f5.com for more on GeoIP."
	::= { ltmTcpanalyticsProfileEntry 7 }

ltmTcpanalyticsProfileCollectCountry OBJECT-TYPE
	SYNTAX INTEGER {
		false(0),
		true(1)
	}
	MAX-ACCESS read-only
	STATUS current
	DESCRIPTION
		"If true, AVR stores the country (from the GeoIP database) for the
	        remote IP address of the connection with TCP statistics. See
	        SOL11176 on support.f5.com for more on GeoIP."
	::= { ltmTcpanalyticsProfileEntry 8 }

ltmTcpanalyticsProfileCollectNexthop OBJECT-TYPE
	SYNTAX INTEGER {
		false(0),
		true(1)
	}
	MAX-ACCESS read-only
	STATUS current
	DESCRIPTION
		"If true, AVR stores the next hop ethernet address of the connection
	        with TCP statistics."
	::= { ltmTcpanalyticsProfileEntry 9 }

ltmTcpanalyticsProfileCollectPostCode OBJECT-TYPE
	SYNTAX INTEGER {
		false(0),
		true(1)
	}
	MAX-ACCESS read-only
	STATUS current
	DESCRIPTION
		"If true, AVR stores the postcode (from the GeoIP database) for the
	        remote IP address of the connection with TCP statistics. See
	        SOL11176 on support.f5.com for more on GeoIP."
	::= { ltmTcpanalyticsProfileEntry 10 }

ltmTcpanalyticsProfileCollectRegion OBJECT-TYPE
	SYNTAX INTEGER {
		false(0),
		true(1)
	}
	MAX-ACCESS read-only
	STATUS current
	DESCRIPTION
		"If true, AVR stores the region (from the GeoIP database) for the
	        remote IP address of the connection with TCP statistics. See
	        SOL11176 on support.f5.com for more on GeoIP."
	::= { ltmTcpanalyticsProfileEntry 11 }

ltmTcpanalyticsProfileCollectRemoteHostIp OBJECT-TYPE
	SYNTAX INTEGER {
		false(0),
		true(1)
	}
	MAX-ACCESS read-only
	STATUS current
	DESCRIPTION
		"If true, AVR stores the remote host IP address with TCP
	        statistics."
	::= { ltmTcpanalyticsProfileEntry 12 }

ltmTcpanalyticsProfileCollectRemoteHostSubnet OBJECT-TYPE
	SYNTAX INTEGER {
		false(0),
		true(1)
	}
	MAX-ACCESS read-only
	STATUS current
	DESCRIPTION
		"If true, AVR stores the remote host IP subnet (24-bit) with TCP
	        statistics."
	::= { ltmTcpanalyticsProfileEntry 13 }

ltmTcpanalyticsProfileCollectedStatsInternalLogging OBJECT-TYPE
	SYNTAX INTEGER {
		false(0),
		true(1)
	}
	MAX-ACCESS read-only
	STATUS current
	DESCRIPTION
		"If true, TCP statistics are logged on the local BIG-IP."
	::= { ltmTcpanalyticsProfileEntry 14 }

ltmTcpanalyticsProfileCollectedStatsExternalLogging OBJECT-TYPE
	SYNTAX INTEGER {
		false(0),
		true(1)
	}
	MAX-ACCESS read-only
	STATUS current
	DESCRIPTION
		"If true, TCP statistics are logged on a remote machine."
	::= { ltmTcpanalyticsProfileEntry 15 }

ltmTcpanalyticsProfileExternalLoggingPublisher OBJECT-TYPE
	SYNTAX LongDisplayString
	MAX-ACCESS read-only
	STATUS current
	DESCRIPTION
		"The name of the publisher to accept external logging."
	::= { ltmTcpanalyticsProfileEntry 16 }

--==================================================================
-- Profile_splitsessionclient
--==================================================================
ltmSplitsessionclientProfileNumber OBJECT-TYPE
	SYNTAX INTEGER
	MAX-ACCESS read-only
	STATUS current
	DESCRIPTION
		"The number of ltmSplitsessionclientProfile entries in the table."
	::= { ltmSplitsessionclientProfile 1 }

ltmSplitsessionclientProfileTable OBJECT-TYPE
	SYNTAX SEQUENCE OF LtmSplitsessionclientProfileEntry
	MAX-ACCESS not-accessible
	STATUS current
	DESCRIPTION
		"A table containing information about the Splitsessionclient profile."
	::= { ltmSplitsessionclientProfile 2 }

ltmSplitsessionclientProfileEntry OBJECT-TYPE
	SYNTAX  LtmSplitsessionclientProfileEntry
	MAX-ACCESS not-accessible
	STATUS current
	DESCRIPTION
		"Columns in the ltmSplitsessionclientProfile Table"
	INDEX {
		ltmSplitsessionclientProfileName
	}
	::= { ltmSplitsessionclientProfileTable 1 }

LtmSplitsessionclientProfileEntry ::=
	SEQUENCE {
        	ltmSplitsessionclientProfileName                          LongDisplayString,
        	ltmSplitsessionclientProfileConfigSource                  INTEGER,
        	ltmSplitsessionclientProfileDefaultName                   LongDisplayString,
        	ltmSplitsessionclientProfilePeerIp                        InetAddressType,
        	ltmSplitsessionclientProfilePeerPort                      InetPortNumber
	}

ltmSplitsessionclientProfileName OBJECT-TYPE
	SYNTAX LongDisplayString
	MAX-ACCESS read-only
	STATUS current
	DESCRIPTION
		"The name of a Splitsessionclient profile."
	::= { ltmSplitsessionclientProfileEntry 1 }

ltmSplitsessionclientProfileConfigSource OBJECT-TYPE
	SYNTAX INTEGER {
		usercfg(0),
		basecfg(1)
	}
	MAX-ACCESS read-only
	STATUS current
	DESCRIPTION
		"The state that specifies whether this is a base/pre-configured profile
		or user defined profile."
	::= { ltmSplitsessionclientProfileEntry 2 }

ltmSplitsessionclientProfileDefaultName OBJECT-TYPE
	SYNTAX LongDisplayString
	MAX-ACCESS read-only
	STATUS current
	DESCRIPTION
		"The name of the profile from which the specified profile derives
		its attribute default values."
	::= { ltmSplitsessionclientProfileEntry 3 }

ltmSplitsessionclientProfilePeerIp OBJECT-TYPE
	SYNTAX InetAddressType
	MAX-ACCESS read-only
	STATUS current
	DESCRIPTION
		"The IP address of the peer that is used for Out-of-band connection."
	::= { ltmSplitsessionclientProfileEntry 4 }

ltmSplitsessionclientProfilePeerPort OBJECT-TYPE
	SYNTAX InetPortNumber
	MAX-ACCESS read-only
	STATUS current
	DESCRIPTION
		"The port of the peer that is used for Out-of-band connection."
	::= { ltmSplitsessionclientProfileEntry 5 }

--==================================================================
-- Profile_splitsessionclient_stat
--==================================================================
ltmSplitsessionclientProfileStatResetStats OBJECT-TYPE
	SYNTAX INTEGER
	MAX-ACCESS read-write
	STATUS current
	DESCRIPTION
		"The action to reset resettable statistics data in ltmSplitsessionclientProfileStat.
		 Setting this value to 1 will reset statistics data.
		 Note, some statistics data may not be reset including data that are incremental counters."
	::= { ltmSplitsessionclientProfileStat 1 }

ltmSplitsessionclientProfileStatNumber OBJECT-TYPE
	SYNTAX INTEGER
	MAX-ACCESS read-only
	STATUS current
	DESCRIPTION
		"The number of ltmSplitsessionclientProfileStat entries in the table."
	::= { ltmSplitsessionclientProfileStat 2 }

ltmSplitsessionclientProfileStatTable OBJECT-TYPE
	SYNTAX SEQUENCE OF LtmSplitsessionclientProfileStatEntry
	MAX-ACCESS not-accessible
	STATUS current
	DESCRIPTION
		"A table containing statistics information about the Splitsessionclient profile."
	::= { ltmSplitsessionclientProfileStat 3 }

ltmSplitsessionclientProfileStatEntry OBJECT-TYPE
	SYNTAX  LtmSplitsessionclientProfileStatEntry
	MAX-ACCESS not-accessible
	STATUS current
	DESCRIPTION
		"Columns in the ltmSplitsessionclientProfileStat Table"
	INDEX {
		ltmSplitsessionclientProfileStatName
	}
	::= { ltmSplitsessionclientProfileStatTable 1 }

LtmSplitsessionclientProfileStatEntry ::=
	SEQUENCE {
        	ltmSplitsessionclientProfileStatName                      LongDisplayString,
        	ltmSplitsessionclientProfileStatConnectionsAccepted       Counter64,
        	ltmSplitsessionclientProfileStatConnectionsCurrent        Counter64,
        	ltmSplitsessionclientProfileStatConnectionsMax            Counter64,
        	ltmSplitsessionclientProfileStatConnPeerActive            Counter64,
        	ltmSplitsessionclientProfileStatConnPeerTimeout           Counter64,
        	ltmSplitsessionclientProfileStatConnPeerReset             Counter64,
        	ltmSplitsessionclientProfileStatPeerMsgRecd               Counter64,
        	ltmSplitsessionclientProfileStatPeerMsgSent               Counter64
	}

ltmSplitsessionclientProfileStatName OBJECT-TYPE
	SYNTAX LongDisplayString
	MAX-ACCESS read-only
	STATUS current
	DESCRIPTION
		"The name of the Splitsessionclient profile."
	::= { ltmSplitsessionclientProfileStatEntry 1 }

ltmSplitsessionclientProfileStatConnectionsAccepted OBJECT-TYPE
	SYNTAX Counter64
	MAX-ACCESS read-only
	STATUS current
	DESCRIPTION
		"The total number of accepted connections."
	::= { ltmSplitsessionclientProfileStatEntry 2 }

ltmSplitsessionclientProfileStatConnectionsCurrent OBJECT-TYPE
	SYNTAX Counter64
	MAX-ACCESS read-only
	STATUS current
	DESCRIPTION
		"The total number of connections currently active."
	::= { ltmSplitsessionclientProfileStatEntry 3 }

ltmSplitsessionclientProfileStatConnectionsMax OBJECT-TYPE
	SYNTAX Counter64
	MAX-ACCESS read-only
	STATUS current
	DESCRIPTION
		"The maximum number of connections open simultaneously."
	::= { ltmSplitsessionclientProfileStatEntry 4 }

ltmSplitsessionclientProfileStatConnPeerActive OBJECT-TYPE
	SYNTAX Counter64
	MAX-ACCESS read-only
	STATUS current
	DESCRIPTION
		"The total number of Out-of-band connections established with the peer."
	::= { ltmSplitsessionclientProfileStatEntry 5 }

ltmSplitsessionclientProfileStatConnPeerTimeout OBJECT-TYPE
	SYNTAX Counter64
	MAX-ACCESS read-only
	STATUS current
	DESCRIPTION
		"The total number of Out-of-band connections that timed out."
	::= { ltmSplitsessionclientProfileStatEntry 6 }

ltmSplitsessionclientProfileStatConnPeerReset OBJECT-TYPE
	SYNTAX Counter64
	MAX-ACCESS read-only
	STATUS current
	DESCRIPTION
		"The total number of Out-of-band connections that were reset."
	::= { ltmSplitsessionclientProfileStatEntry 7 }

ltmSplitsessionclientProfileStatPeerMsgRecd OBJECT-TYPE
	SYNTAX Counter64
	MAX-ACCESS read-only
	STATUS current
	DESCRIPTION
		"The total number of messages received over the Out-of-band connections."
	::= { ltmSplitsessionclientProfileStatEntry 8 }

ltmSplitsessionclientProfileStatPeerMsgSent OBJECT-TYPE
	SYNTAX Counter64
	MAX-ACCESS read-only
	STATUS current
	DESCRIPTION
		"The total number of messages sent over the Out-of-band connections."
	::= { ltmSplitsessionclientProfileStatEntry 9 }

--==================================================================
-- Profile_splitsessionserver
--==================================================================
ltmSplitsessionserverProfileNumber OBJECT-TYPE
	SYNTAX INTEGER
	MAX-ACCESS read-only
	STATUS current
	DESCRIPTION
		"The number of ltmSplitsessionserverProfile entries in the table."
	::= { ltmSplitsessionserverProfile 1 }

ltmSplitsessionserverProfileTable OBJECT-TYPE
	SYNTAX SEQUENCE OF LtmSplitsessionserverProfileEntry
	MAX-ACCESS not-accessible
	STATUS current
	DESCRIPTION
		"A table containing information about the Splitsessionserver profile."
	::= { ltmSplitsessionserverProfile 2 }

ltmSplitsessionserverProfileEntry OBJECT-TYPE
	SYNTAX  LtmSplitsessionserverProfileEntry
	MAX-ACCESS not-accessible
	STATUS current
	DESCRIPTION
		"Columns in the ltmSplitsessionserverProfile Table"
	INDEX {
		ltmSplitsessionserverProfileName
	}
	::= { ltmSplitsessionserverProfileTable 1 }

LtmSplitsessionserverProfileEntry ::=
	SEQUENCE {
        	ltmSplitsessionserverProfileName                          LongDisplayString,
        	ltmSplitsessionserverProfileConfigSource                  INTEGER,
        	ltmSplitsessionserverProfileDefaultName                   LongDisplayString,
        	ltmSplitsessionserverProfileListenIp                      InetAddressType,
        	ltmSplitsessionserverProfileListenPort                    InetPortNumber
	}

ltmSplitsessionserverProfileName OBJECT-TYPE
	SYNTAX LongDisplayString
	MAX-ACCESS read-only
	STATUS current
	DESCRIPTION
		"The name of a Splitsessionserver profile."
	::= { ltmSplitsessionserverProfileEntry 1 }

ltmSplitsessionserverProfileConfigSource OBJECT-TYPE
	SYNTAX INTEGER {
		usercfg(0),
		basecfg(1)
	}
	MAX-ACCESS read-only
	STATUS current
	DESCRIPTION
		"The state that specifies whether this is a base/pre-configured profile
		or user defined profile."
	::= { ltmSplitsessionserverProfileEntry 2 }

ltmSplitsessionserverProfileDefaultName OBJECT-TYPE
	SYNTAX LongDisplayString
	MAX-ACCESS read-only
	STATUS current
	DESCRIPTION
		"The name of the profile from which the specified profile derives
		its attribute default values."
	::= { ltmSplitsessionserverProfileEntry 3 }

ltmSplitsessionserverProfileListenIp OBJECT-TYPE
	SYNTAX InetAddressType
	MAX-ACCESS read-only
	STATUS current
	DESCRIPTION
		"The IP address that the peer uses to connect for Out-of-band connection."
	::= { ltmSplitsessionserverProfileEntry 4 }

ltmSplitsessionserverProfileListenPort OBJECT-TYPE
	SYNTAX InetPortNumber
	MAX-ACCESS read-only
	STATUS current
	DESCRIPTION
		"The port that the peer uses to connect for Out-of-band connection."
	::= { ltmSplitsessionserverProfileEntry 5 }

--==================================================================
-- Profile_splitsessionserver_stat
--==================================================================
ltmSplitsessionserverProfileStatResetStats OBJECT-TYPE
	SYNTAX INTEGER
	MAX-ACCESS read-write
	STATUS current
	DESCRIPTION
		"The action to reset resettable statistics data in ltmSplitsessionserverProfileStat.
		 Setting this value to 1 will reset statistics data.
		 Note, some statistics data may not be reset including data that are incremental counters."
	::= { ltmSplitsessionserverProfileStat 1 }

ltmSplitsessionserverProfileStatNumber OBJECT-TYPE
	SYNTAX INTEGER
	MAX-ACCESS read-only
	STATUS current
	DESCRIPTION
		"The number of ltmSplitsessionserverProfileStat entries in the table."
	::= { ltmSplitsessionserverProfileStat 2 }

ltmSplitsessionserverProfileStatTable OBJECT-TYPE
	SYNTAX SEQUENCE OF LtmSplitsessionserverProfileStatEntry
	MAX-ACCESS not-accessible
	STATUS current
	DESCRIPTION
		"A table containing statistics information about the Splitsessionserver profile."
	::= { ltmSplitsessionserverProfileStat 3 }

ltmSplitsessionserverProfileStatEntry OBJECT-TYPE
	SYNTAX  LtmSplitsessionserverProfileStatEntry
	MAX-ACCESS not-accessible
	STATUS current
	DESCRIPTION
		"Columns in the ltmSplitsessionserverProfileStat Table"
	INDEX {
		ltmSplitsessionserverProfileStatName
	}
	::= { ltmSplitsessionserverProfileStatTable 1 }

LtmSplitsessionserverProfileStatEntry ::=
	SEQUENCE {
        	ltmSplitsessionserverProfileStatName                      LongDisplayString,
        	ltmSplitsessionserverProfileStatConnectionsAccepted       Counter64,
        	ltmSplitsessionserverProfileStatConnectionsCurrent        Counter64,
        	ltmSplitsessionserverProfileStatConnectionsMax            Counter64,
        	ltmSplitsessionserverProfileStatConnPeerActive            Counter64,
        	ltmSplitsessionserverProfileStatConnPeerTimeout           Counter64,
        	ltmSplitsessionserverProfileStatConnPeerReset             Counter64,
        	ltmSplitsessionserverProfileStatPeerMsgRecd               Counter64,
        	ltmSplitsessionserverProfileStatPeerMsgSent               Counter64
	}

ltmSplitsessionserverProfileStatName OBJECT-TYPE
	SYNTAX LongDisplayString
	MAX-ACCESS read-only
	STATUS current
	DESCRIPTION
		"The name of the Splitsessionserver profile."
	::= { ltmSplitsessionserverProfileStatEntry 1 }

ltmSplitsessionserverProfileStatConnectionsAccepted OBJECT-TYPE
	SYNTAX Counter64
	MAX-ACCESS read-only
	STATUS current
	DESCRIPTION
		"The total number of accepted connections."
	::= { ltmSplitsessionserverProfileStatEntry 2 }

ltmSplitsessionserverProfileStatConnectionsCurrent OBJECT-TYPE
	SYNTAX Counter64
	MAX-ACCESS read-only
	STATUS current
	DESCRIPTION
		"The total number of connections currently active."
	::= { ltmSplitsessionserverProfileStatEntry 3 }

ltmSplitsessionserverProfileStatConnectionsMax OBJECT-TYPE
	SYNTAX Counter64
	MAX-ACCESS read-only
	STATUS current
	DESCRIPTION
		"The maximum number of connections open simultaneously."
	::= { ltmSplitsessionserverProfileStatEntry 4 }

ltmSplitsessionserverProfileStatConnPeerActive OBJECT-TYPE
	SYNTAX Counter64
	MAX-ACCESS read-only
	STATUS current
	DESCRIPTION
		"The total number of Out-of-band connections established with the peer."
	::= { ltmSplitsessionserverProfileStatEntry 5 }

ltmSplitsessionserverProfileStatConnPeerTimeout OBJECT-TYPE
	SYNTAX Counter64
	MAX-ACCESS read-only
	STATUS current
	DESCRIPTION
		"The total number of Out-of-band connections that timed out."
	::= { ltmSplitsessionserverProfileStatEntry 6 }

ltmSplitsessionserverProfileStatConnPeerReset OBJECT-TYPE
	SYNTAX Counter64
	MAX-ACCESS read-only
	STATUS current
	DESCRIPTION
		"The total number of Out-of-band connections that were reset."
	::= { ltmSplitsessionserverProfileStatEntry 7 }

ltmSplitsessionserverProfileStatPeerMsgRecd OBJECT-TYPE
	SYNTAX Counter64
	MAX-ACCESS read-only
	STATUS current
	DESCRIPTION
		"The total number of messages received over the Out-of-band connections."
	::= { ltmSplitsessionserverProfileStatEntry 8 }

ltmSplitsessionserverProfileStatPeerMsgSent OBJECT-TYPE
	SYNTAX Counter64
	MAX-ACCESS read-only
	STATUS current
	DESCRIPTION
		"The total number of messages sent over the Out-of-band connections."
	::= { ltmSplitsessionserverProfileStatEntry 9 }

--==================================================================
-- Profile_http_proxy_connect
--==================================================================
ltmHttpProxyConnectProfileNumber OBJECT-TYPE
	SYNTAX INTEGER
	MAX-ACCESS read-only
	STATUS current
	DESCRIPTION
		"The number of ltmHttpProxyConnectProfile entries in the table."
	::= { ltmHttpProxyConnectProfile 1 }

ltmHttpProxyConnectProfileTable OBJECT-TYPE
	SYNTAX SEQUENCE OF LtmHttpProxyConnectProfileEntry
	MAX-ACCESS not-accessible
	STATUS current
	DESCRIPTION
		"A table containing information about the HTTP Proxy Connect profile."
	::= { ltmHttpProxyConnectProfile 2 }

ltmHttpProxyConnectProfileEntry OBJECT-TYPE
	SYNTAX  LtmHttpProxyConnectProfileEntry
	MAX-ACCESS not-accessible
	STATUS current
	DESCRIPTION
		"Columns in the ltmHttpProxyConnectProfile Table"
	INDEX {
		ltmHttpProxyConnectProfileName
	}
	::= { ltmHttpProxyConnectProfileTable 1 }

LtmHttpProxyConnectProfileEntry ::=
	SEQUENCE {
        	ltmHttpProxyConnectProfileName                            LongDisplayString,
        	ltmHttpProxyConnectProfileConfigSource                    INTEGER,
        	ltmHttpProxyConnectProfileDefaultName                     LongDisplayString,
        	ltmHttpProxyConnectProfileDefaultState                    INTEGER
	}

ltmHttpProxyConnectProfileName OBJECT-TYPE
	SYNTAX LongDisplayString
	MAX-ACCESS read-only
	STATUS current
	DESCRIPTION
		"The name of a HTTP Proxy Connect profile."
	::= { ltmHttpProxyConnectProfileEntry 1 }

ltmHttpProxyConnectProfileConfigSource OBJECT-TYPE
	SYNTAX INTEGER {
		usercfg(0),
		basecfg(1)
	}
	MAX-ACCESS read-only
	STATUS current
	DESCRIPTION
		"The state that specifies whether this is a base/pre-configured profile
		or user defined profile."
	::= { ltmHttpProxyConnectProfileEntry 2 }

ltmHttpProxyConnectProfileDefaultName OBJECT-TYPE
	SYNTAX LongDisplayString
	MAX-ACCESS read-only
	STATUS current
	DESCRIPTION
		"The name of the profile from which the specified profile derives
		its attribute default values."
	::= { ltmHttpProxyConnectProfileEntry 3 }

ltmHttpProxyConnectProfileDefaultState OBJECT-TYPE
	SYNTAX INTEGER {
		false(0),
		true(1)
	}
	MAX-ACCESS read-only
	STATUS current
	DESCRIPTION
		"Enable proxy chaining by default, or not."
	::= { ltmHttpProxyConnectProfileEntry 4 }

--==================================================================
-- Profile_http_proxy_connect_stat
--==================================================================
ltmHttpProxyConnectProfileStatResetStats OBJECT-TYPE
	SYNTAX INTEGER
	MAX-ACCESS read-write
	STATUS current
	DESCRIPTION
		"The action to reset resettable statistics data in ltmHttpProxyConnectProfileStat.
		 Setting this value to 1 will reset statistics data.
		 Note, some statistics data may not be reset including data that are incremental counters."
	::= { ltmHttpProxyConnectProfileStat 1 }

ltmHttpProxyConnectProfileStatNumber OBJECT-TYPE
	SYNTAX INTEGER
	MAX-ACCESS read-only
	STATUS current
	DESCRIPTION
		"The number of ltmHttpProxyConnectProfileStat entries in the table."
	::= { ltmHttpProxyConnectProfileStat 2 }

ltmHttpProxyConnectProfileStatTable OBJECT-TYPE
	SYNTAX SEQUENCE OF LtmHttpProxyConnectProfileStatEntry
	MAX-ACCESS not-accessible
	STATUS current
	DESCRIPTION
		"A table containing statistic information of HTTP Proxy Connect profiles."
	::= { ltmHttpProxyConnectProfileStat 3 }

ltmHttpProxyConnectProfileStatEntry OBJECT-TYPE
	SYNTAX  LtmHttpProxyConnectProfileStatEntry
	MAX-ACCESS not-accessible
	STATUS current
	DESCRIPTION
		"Columns in the ltmHttpProxyConnectProfileStat Table"
	INDEX {
		ltmHttpProxyConnectProfileStatName
	}
	::= { ltmHttpProxyConnectProfileStatTable 1 }

LtmHttpProxyConnectProfileStatEntry ::=
	SEQUENCE {
        	ltmHttpProxyConnectProfileStatName                        LongDisplayString,
        	ltmHttpProxyConnectProfileStatResp2xxCnt                  Counter64,
        	ltmHttpProxyConnectProfileStatResp3xxCnt                  Counter64,
        	ltmHttpProxyConnectProfileStatResp4xxCnt                  Counter64,
        	ltmHttpProxyConnectProfileStatResp5xxCnt                  Counter64,
        	ltmHttpProxyConnectProfileStatRespOtherCnt                Counter64,
        	ltmHttpProxyConnectProfileStatV9Resp                      Counter64,
        	ltmHttpProxyConnectProfileStatV10Resp                     Counter64,
        	ltmHttpProxyConnectProfileStatV11Resp                     Counter64,
        	ltmHttpProxyConnectProfileStatProxyConnReqs               Counter64
	}

ltmHttpProxyConnectProfileStatName OBJECT-TYPE
	SYNTAX LongDisplayString
	MAX-ACCESS read-only
	STATUS current
	DESCRIPTION
		"The name of a HTTP Proxy Connect profile."
	::= { ltmHttpProxyConnectProfileStatEntry 1 }

ltmHttpProxyConnectProfileStatResp2xxCnt OBJECT-TYPE
	SYNTAX Counter64
	MAX-ACCESS read-only
	STATUS current
	DESCRIPTION
		"The number of server-side responses in range of 200 to 206
		 (successful responses)"
	::= { ltmHttpProxyConnectProfileStatEntry 2 }

ltmHttpProxyConnectProfileStatResp3xxCnt OBJECT-TYPE
	SYNTAX Counter64
	MAX-ACCESS read-only
	STATUS current
	DESCRIPTION
		"The number of server-side responses in range of 300 to 307
		 (redirection responses)."
	::= { ltmHttpProxyConnectProfileStatEntry 3 }

ltmHttpProxyConnectProfileStatResp4xxCnt OBJECT-TYPE
	SYNTAX Counter64
	MAX-ACCESS read-only
	STATUS current
	DESCRIPTION
		"The number of server-side responses in range of 400 to 417
		 (client errors)."
	::= { ltmHttpProxyConnectProfileStatEntry 4 }

ltmHttpProxyConnectProfileStatResp5xxCnt OBJECT-TYPE
	SYNTAX Counter64
	MAX-ACCESS read-only
	STATUS current
	DESCRIPTION
		"The number of server-side responses in range of 500 to 505
		 (server errors)."
	::= { ltmHttpProxyConnectProfileStatEntry 5 }

ltmHttpProxyConnectProfileStatRespOtherCnt OBJECT-TYPE
	SYNTAX Counter64
	MAX-ACCESS read-only
	STATUS current
	DESCRIPTION
		"The number of server-side responses with other status ids."
	::= { ltmHttpProxyConnectProfileStatEntry 6 }

ltmHttpProxyConnectProfileStatV9Resp OBJECT-TYPE
	SYNTAX Counter64
	MAX-ACCESS read-only
	STATUS current
	DESCRIPTION
		"The total number of version 9 responses."
	::= { ltmHttpProxyConnectProfileStatEntry 7 }

ltmHttpProxyConnectProfileStatV10Resp OBJECT-TYPE
	SYNTAX Counter64
	MAX-ACCESS read-only
	STATUS current
	DESCRIPTION
		"The total number of version 10 responses."
	::= { ltmHttpProxyConnectProfileStatEntry 8 }

ltmHttpProxyConnectProfileStatV11Resp OBJECT-TYPE
	SYNTAX Counter64
	MAX-ACCESS read-only
	STATUS current
	DESCRIPTION
		"The total number of version 11 responses."
	::= { ltmHttpProxyConnectProfileStatEntry 9 }

ltmHttpProxyConnectProfileStatProxyConnReqs OBJECT-TYPE
	SYNTAX Counter64
	MAX-ACCESS read-only
	STATUS current
	DESCRIPTION
		"The total number of CONNECT requests."
	::= { ltmHttpProxyConnectProfileStatEntry 10 }

--==================================================================
-- Profile_diametersession
--==================================================================
ltmDiametersessionProfileNumber OBJECT-TYPE
	SYNTAX INTEGER
	MAX-ACCESS read-only
	STATUS current
	DESCRIPTION
		"The number of ltmDiametersessionProfile entries in the table."
	::= { ltmDiametersessionProfile 1 }

ltmDiametersessionProfileTable OBJECT-TYPE
	SYNTAX SEQUENCE OF LtmDiametersessionProfileEntry
	MAX-ACCESS not-accessible
	STATUS current
	DESCRIPTION
		"A table containing configuration information for diameter session profiles."
	::= { ltmDiametersessionProfile 2 }

ltmDiametersessionProfileEntry OBJECT-TYPE
	SYNTAX  LtmDiametersessionProfileEntry
	MAX-ACCESS not-accessible
	STATUS current
	DESCRIPTION
		"Columns in the ltmDiametersessionProfile Table"
	INDEX {
		ltmDiametersessionProfileName
	}
	::= { ltmDiametersessionProfileTable 1 }

LtmDiametersessionProfileEntry ::=
	SEQUENCE {
        	ltmDiametersessionProfileName                             LongDisplayString,
        	ltmDiametersessionProfileConfigSource                     INTEGER,
        	ltmDiametersessionProfileDefaultName                      LongDisplayString,
        	ltmDiametersessionProfileRouteUnconfiguredPeers           INTEGER,
        	ltmDiametersessionProfileHandshakeTimeout                 Gauge,
        	ltmDiametersessionProfileMaxRetransmissions               Gauge,
        	ltmDiametersessionProfileMaxWatchdogFailures              Gauge,
        	ltmDiametersessionProfileResetOnTimeout                   INTEGER,
        	ltmDiametersessionProfileRetransmissionTimeout            Gauge,
        	ltmDiametersessionProfileRetransmissionAction             Gauge,
        	ltmDiametersessionProfileArrayRetransmissionErrorCode     LongDisplayString,
        	ltmDiametersessionProfileRetransmissionQueueMaxMessages   Gauge,
        	ltmDiametersessionProfileRetransmissionQueueMaxBytes      Gauge,
        	ltmDiametersessionProfileRetransmissionQueueLimitHigh     Gauge,
        	ltmDiametersessionProfileRetransmissionQueueLimitLow      Gauge,
        	ltmDiametersessionProfileDiscardUnroutable                INTEGER,
        	ltmDiametersessionProfileLoopDetection                    INTEGER,
        	ltmDiametersessionProfileWatchdogTimeout                  Gauge,
        	ltmDiametersessionProfileMaxMessageSize                   Gauge,
        	ltmDiametersessionProfilePersistType                      Gauge,
        	ltmDiametersessionProfilePersistAvp                       LongDisplayString,
        	ltmDiametersessionProfilePersistTimeout                   Gauge,
        	ltmDiametersessionProfileOriginHostRewrite                LongDisplayString,
        	ltmDiametersessionProfileOriginRealmRewrite               LongDisplayString,
        	ltmDiametersessionProfileDestHostRewrite                  LongDisplayString,
        	ltmDiametersessionProfileDestRealmRewrite                 LongDisplayString,
        	ltmDiametersessionProfileOriginHost                       LongDisplayString,
        	ltmDiametersessionProfileOriginRealm                      LongDisplayString,
        	ltmDiametersessionProfileHostIpAddress                    LongDisplayString,
        	ltmDiametersessionProfileVendorId                         Gauge,
        	ltmDiametersessionProfileFirmwareRevision                 Gauge,
        	ltmDiametersessionProfileProductName                      LongDisplayString,
        	ltmDiametersessionProfileAuthApplicationId                Gauge,
        	ltmDiametersessionProfileAcctApplicationId                Gauge,
        	ltmDiametersessionProfileArrayAuthApplicationId           LongDisplayString,
        	ltmDiametersessionProfileArrayAcctApplicationId           LongDisplayString,
        	ltmDiametersessionProfileVendorSpecificVendorId           Gauge,
        	ltmDiametersessionProfileVendorSpecificAuthApplicationId  Gauge,
        	ltmDiametersessionProfileVendorSpecificAcctApplicationId  Gauge,
        	ltmDiametersessionProfilePeerDelayCriticalLimit           Gauge,
        	ltmDiametersessionProfileEgressCriticalMessageRateLimit   Gauge,
        	ltmDiametersessionProfileEgressMajorMessageRateLimit      Gauge,
        	ltmDiametersessionProfileIngressCriticalMessageRateLimit  Gauge,
        	ltmDiametersessionProfileIngressMajorMessageRateLimit     Gauge,
        	ltmDiametersessionProfileDynamicRouteInsertion            INTEGER,
        	ltmDiametersessionProfileDynamicRouteLookup               INTEGER,
        	ltmDiametersessionProfileDynamicRouteTimeout              Gauge,
        	ltmDiametersessionProfilePeerErrorsMajorThreshold         Gauge,
        	ltmDiametersessionProfilePeerTimeoutsMajorThreshold       Gauge,
        	ltmDiametersessionProfileDisconnectPeerAction             Gauge
	}

ltmDiametersessionProfileName OBJECT-TYPE
	SYNTAX LongDisplayString
	MAX-ACCESS read-only
	STATUS current
	DESCRIPTION
		"The Name of the diametersession profile."
	::= { ltmDiametersessionProfileEntry 1 }

ltmDiametersessionProfileConfigSource OBJECT-TYPE
	SYNTAX INTEGER {
		usercfg(0),
		basecfg(1)
	}
	MAX-ACCESS read-only
	STATUS current
	DESCRIPTION
		"The state that specifies whether this is a base/pre-configured profile
	      or user defined profile."
	::= { ltmDiametersessionProfileEntry 2 }

ltmDiametersessionProfileDefaultName OBJECT-TYPE
	SYNTAX LongDisplayString
	MAX-ACCESS read-only
	STATUS current
	DESCRIPTION
		"The name of the profile from which the specified profile derives
	      its attribute default values."
	::= { ltmDiametersessionProfileEntry 3 }

ltmDiametersessionProfileRouteUnconfiguredPeers OBJECT-TYPE
	SYNTAX INTEGER {
		false(0),
		true(1)
	}
	MAX-ACCESS read-only
	STATUS current
	DESCRIPTION
		"When it is
	    enabled, unconfigured peers is added to the route table."
	::= { ltmDiametersessionProfileEntry 4 }

ltmDiametersessionProfileHandshakeTimeout OBJECT-TYPE
	SYNTAX Gauge
	MAX-ACCESS read-only
	STATUS current
	DESCRIPTION
		"Indicates the number of seconds
	    before the handshake times out to a peer."
	::= { ltmDiametersessionProfileEntry 5 }

ltmDiametersessionProfileMaxRetransmissions OBJECT-TYPE
	SYNTAX Gauge
	MAX-ACCESS read-only
	STATUS current
	DESCRIPTION
		"Number of times, the peer tries to
	    retransmit the message."
	::= { ltmDiametersessionProfileEntry 6 }

ltmDiametersessionProfileMaxWatchdogFailures OBJECT-TYPE
	SYNTAX Gauge
	MAX-ACCESS read-only
	STATUS current
	DESCRIPTION
		"Specifies the maximum number of
	    device watchdog failures that the traffic management system can
	    take before it tears down the connection. After the system
	    receives this number of device watchdog failures, it closes the
	    connection if the reset-on-timeout is enabled. However, if the
	    reset-on-timeout is not enabled, but the watchdog timeout count is
	    great and equal than 3 times of max-watchdog-failures, then the
	    connection is closed."
	::= { ltmDiametersessionProfileEntry 7 }

ltmDiametersessionProfileResetOnTimeout OBJECT-TYPE
	SYNTAX INTEGER {
		false(0),
		true(1)
	}
	MAX-ACCESS read-only
	STATUS current
	DESCRIPTION
		"When it is enabled
	    and the watchdog failures exceed the max watchdog failure, the
	    system resets the connection. The default value is enabled."
	::= { ltmDiametersessionProfileEntry 8 }

ltmDiametersessionProfileRetransmissionTimeout OBJECT-TYPE
	SYNTAX Gauge
	MAX-ACCESS read-only
	STATUS current
	DESCRIPTION
		"Specifies the retransmission
	    timeout in seconds. This setting specifies the number of seconds
	    the BIG-IP waits to retransmit the request messages if it does not
	    receive the corresponding answer messages. The default value is
	    10."
	::= { ltmDiametersessionProfileEntry 9 }

ltmDiametersessionProfileRetransmissionAction OBJECT-TYPE
	SYNTAX Gauge
	MAX-ACCESS read-only
	STATUS current
	DESCRIPTION
		"Specifies the action to be
	    performed when retransmission is triggered for a request message.
	    disable: retransmission is disabled busy: A busy answer is sent to
	    the originator of the request unavailable: A unable to deliver
	    answer is sent to the originator of the request retransmit: the
	    request message will be retransmitted."
	::= { ltmDiametersessionProfileEntry 10 }

ltmDiametersessionProfileArrayRetransmissionErrorCode OBJECT-TYPE
	SYNTAX LongDisplayString
	MAX-ACCESS read-only
	STATUS current
	DESCRIPTION
		"Specifies a list of
	    DIAMETER error codes that if an answer message is received
	    containing one of the listed error codes, the corresponding
	    request will be retransmitted as directed by the
	    retransmission-action.  Each error-code in the list is limited
	    from 1000 to 6999"
	::= { ltmDiametersessionProfileEntry 11 }

ltmDiametersessionProfileRetransmissionQueueMaxMessages OBJECT-TYPE
	SYNTAX Gauge
	MAX-ACCESS read-only
	STATUS current
	DESCRIPTION
		"Specifies the
	    maximum number of messages that may be held in the retransmission
	    message queue. If a request message is received that is enabled
	    for retransmission and the retransmission queue has reached its
	    configured limit, a busy answer will be returned to the
	    originator. A value of zero disables the limit."
	::= { ltmDiametersessionProfileEntry 12 }

ltmDiametersessionProfileRetransmissionQueueMaxBytes OBJECT-TYPE
	SYNTAX Gauge
	MAX-ACCESS read-only
	STATUS current
	DESCRIPTION
		"Specifies the maximum
	    number of bytes that may be held in the retransmission message
	    queue. If a request message is received that is enabled for
	    retransmission and the retransmission queue has reached its
	    configured limit, a busy answer will be returned to the
	    originator. A value of zero disables the limit."
	::= { ltmDiametersessionProfileEntry 13 }

ltmDiametersessionProfileRetransmissionQueueLimitHigh OBJECT-TYPE
	SYNTAX Gauge
	MAX-ACCESS read-only
	STATUS current
	DESCRIPTION
		"Specifies the high
	    watermark for the retransmission queue in percent. If the number
	    of messages or bytes in the retransmission queue for a connection
	    exceeds the high watermark, the TCP window will begin to close. If
	    zero value disables closing the TCP window based on queue size."
	::= { ltmDiametersessionProfileEntry 14 }

ltmDiametersessionProfileRetransmissionQueueLimitLow OBJECT-TYPE
	SYNTAX Gauge
	MAX-ACCESS read-only
	STATUS current
	DESCRIPTION
		"Specifies the low
	    watermark for the retransmission queue in percent. If the number
	    of messages or bytes in the retransmission queue for a connection
	    drops below the low watermark, the TCP window will reopen."
	::= { ltmDiametersessionProfileEntry 15 }

ltmDiametersessionProfileDiscardUnroutable OBJECT-TYPE
	SYNTAX INTEGER {
		false(0),
		true(1)
	}
	MAX-ACCESS read-only
	STATUS current
	DESCRIPTION
		"If enabled,
	    discard unroutable messages."
	::= { ltmDiametersessionProfileEntry 16 }

ltmDiametersessionProfileLoopDetection OBJECT-TYPE
	SYNTAX INTEGER {
		false(0),
		true(1)
	}
	MAX-ACCESS read-only
	STATUS current
	DESCRIPTION
		"If enabled, detect and
	    reject (error response) looped request messages."
	::= { ltmDiametersessionProfileEntry 17 }

ltmDiametersessionProfileWatchdogTimeout OBJECT-TYPE
	SYNTAX Gauge
	MAX-ACCESS read-only
	STATUS current
	DESCRIPTION
		"Specifies the watchdog timeout in
	    seconds. This setting specifies the number of seconds that a
	    connection is idle before the device watchdog request is sent. The
	    default value is 0, which means BIG-IP will not send a device
	    watchdog request to either client or server side."
	::= { ltmDiametersessionProfileEntry 18 }

ltmDiametersessionProfileMaxMessageSize OBJECT-TYPE
	SYNTAX Gauge
	MAX-ACCESS read-only
	STATUS current
	DESCRIPTION
		"Maximum bytes that will be allowed
	    for the messages. The default value is 0, which means no such
	    restriction is allowed in BIG-IP."
	::= { ltmDiametersessionProfileEntry 19 }

ltmDiametersessionProfilePersistType OBJECT-TYPE
	SYNTAX Gauge
	MAX-ACCESS read-only
	STATUS current
	DESCRIPTION
		"Specifies the type of the persistence.
	       None - Persistence is disabled
	       AVP - To persist based on avp in the message.
	       Custom - To persist based on the custom key specified using iRule."
	::= { ltmDiametersessionProfileEntry 20 }

ltmDiametersessionProfilePersistAvp OBJECT-TYPE
	SYNTAX LongDisplayString
	MAX-ACCESS read-only
	STATUS current
	DESCRIPTION
		"Specifies the Diameter AVP that is used
	    for persistence. The format is avp[index] for a single AVP or
	    a[x]:b[y]:c[z]:d[w] for a grouped AVP. There may be at most 4 AVPs
	    in a group. The AVP name is used as the session-key; it may be an
	    ASCII string or numeric ID in the range 1 to 4294967295 (AVP code
	    can be specified instead of AVP name). The default value is
	    'SESSION-ID[0]'. A grouped-avp can be specified with the following
	    syntax:
	    grouped-avp-name[index]:nested-avp1[index1]:nested-avp2[index2],
	    where nested-avp1 and nested-avp2 are the AVPs in the grouped
	    AVP."
	::= { ltmDiametersessionProfileEntry 21 }

ltmDiametersessionProfilePersistTimeout OBJECT-TYPE
	SYNTAX Gauge
	MAX-ACCESS read-only
	STATUS current
	DESCRIPTION
		"Indicates the timeout value for
	    persistence entries in seconds. Its recommended to have the
	    persist-timeout to be greater than transaction timeout, specified
	    in the Diameter router configuration, as the lesser of the two is
	    used when creating the persist record on receiving of the first
	    Diameter request message. Upon receiving of the response for the
	    first Diameter request message the persistence record is updated
	    with the persist-timeout value. (For any subsequent responses
	    received the persist timeout is updated for the persist
	    record.)"
	::= { ltmDiametersessionProfileEntry 22 }

ltmDiametersessionProfileOriginHostRewrite OBJECT-TYPE
	SYNTAX LongDisplayString
	MAX-ACCESS read-only
	STATUS current
	DESCRIPTION
		"Rewrites the Origin-Host AVP to
	    the specified value on the egress."
	::= { ltmDiametersessionProfileEntry 23 }

ltmDiametersessionProfileOriginRealmRewrite OBJECT-TYPE
	SYNTAX LongDisplayString
	MAX-ACCESS read-only
	STATUS current
	DESCRIPTION
		"Rewrites the Origin-Host AVP to
	    the specified value on the egress."
	::= { ltmDiametersessionProfileEntry 24 }

ltmDiametersessionProfileDestHostRewrite OBJECT-TYPE
	SYNTAX LongDisplayString
	MAX-ACCESS read-only
	STATUS current
	DESCRIPTION
		"Rewrites the Destination-Host AVP
	    to the specified value on the egress."
	::= { ltmDiametersessionProfileEntry 25 }

ltmDiametersessionProfileDestRealmRewrite OBJECT-TYPE
	SYNTAX LongDisplayString
	MAX-ACCESS read-only
	STATUS current
	DESCRIPTION
		"Rewrites the Destination-Realm AVP
	    to the specified value on the egress."
	::= { ltmDiametersessionProfileEntry 26 }

ltmDiametersessionProfileOriginHost OBJECT-TYPE
	SYNTAX LongDisplayString
	MAX-ACCESS read-only
	STATUS current
	DESCRIPTION
		"Specifies the identifier of the
	    originating server in the form siteserver.f5.com. Must specify the
	    origin-host."
	::= { ltmDiametersessionProfileEntry 27 }

ltmDiametersessionProfileOriginRealm OBJECT-TYPE
	SYNTAX LongDisplayString
	MAX-ACCESS read-only
	STATUS current
	DESCRIPTION
		"Origin-Realm AVP data. Must specify the
	    origin-realm."
	::= { ltmDiametersessionProfileEntry 28 }

ltmDiametersessionProfileHostIpAddress OBJECT-TYPE
	SYNTAX LongDisplayString
	MAX-ACCESS read-only
	STATUS current
	DESCRIPTION
		"Specifies the IP address of the
	    diameter server. If no value is specified, the system uses the
	    BIG-IP system's IP address on the VLAN that the system uses to
	    generate traffic to the server."
	::= { ltmDiametersessionProfileEntry 29 }

ltmDiametersessionProfileVendorId OBJECT-TYPE
	SYNTAX Gauge
	MAX-ACCESS read-only
	STATUS current
	DESCRIPTION
		"Specifies the vendor identification number
	    assigned to your diameter server by the Internet Assigned Numbers
	    Authority (IANA). The default is 0."
	::= { ltmDiametersessionProfileEntry 30 }

ltmDiametersessionProfileFirmwareRevision OBJECT-TYPE
	SYNTAX Gauge
	MAX-ACCESS read-only
	STATUS current
	DESCRIPTION
		"Specifies the firmware revision of
	    the issuing device to inform a diameter peer. The default value
	    is 1."
	::= { ltmDiametersessionProfileEntry 31 }

ltmDiametersessionProfileProductName OBJECT-TYPE
	SYNTAX LongDisplayString
	MAX-ACCESS read-only
	STATUS current
	DESCRIPTION
		"Specifies the vendor-assigned name for
	    the product."
	::= { ltmDiametersessionProfileEntry 32 }

ltmDiametersessionProfileAuthApplicationId OBJECT-TYPE
	SYNTAX Gauge
	MAX-ACCESS read-only
	STATUS current
	DESCRIPTION
		"Specifies the Authentication and
	    Authorization identifier for a specific application, as specified
	    in RFC 6733."
	::= { ltmDiametersessionProfileEntry 33 }

ltmDiametersessionProfileAcctApplicationId OBJECT-TYPE
	SYNTAX Gauge
	MAX-ACCESS read-only
	STATUS current
	DESCRIPTION
		"Specifies the Accounting
	    identifier for a specific application, as specified in RFC
	    6733."
	::= { ltmDiametersessionProfileEntry 34 }

ltmDiametersessionProfileArrayAuthApplicationId OBJECT-TYPE
	SYNTAX LongDisplayString
	MAX-ACCESS read-only
	STATUS current
	DESCRIPTION
		"Specifies a space separted
	    list of Authentication and Authorization identifiers for a
	    specific application, as specified in RFC 6733."
	::= { ltmDiametersessionProfileEntry 35 }

ltmDiametersessionProfileArrayAcctApplicationId OBJECT-TYPE
	SYNTAX LongDisplayString
	MAX-ACCESS read-only
	STATUS current
	DESCRIPTION
		"Specifies a space separated
	    list of Accounting identifiers for a specific application, as
	    specified in RFC 6733."
	::= { ltmDiametersessionProfileEntry 36 }

ltmDiametersessionProfileVendorSpecificVendorId OBJECT-TYPE
	SYNTAX Gauge
	MAX-ACCESS read-only
	STATUS current
	DESCRIPTION
		"Specifies the vendor
	    identification number for the vendor-specific application."
	::= { ltmDiametersessionProfileEntry 37 }

ltmDiametersessionProfileVendorSpecificAuthApplicationId OBJECT-TYPE
	SYNTAX Gauge
	MAX-ACCESS read-only
	STATUS current
	DESCRIPTION
		"Specifies the
	    authentication identification number for the vendor-specific
	    application."
	::= { ltmDiametersessionProfileEntry 38 }

ltmDiametersessionProfileVendorSpecificAcctApplicationId OBJECT-TYPE
	SYNTAX Gauge
	MAX-ACCESS read-only
	STATUS current
	DESCRIPTION
		"Specifies the
	    accounting identification number for the vendor-specific
	    application."
	::= { ltmDiametersessionProfileEntry 39 }

ltmDiametersessionProfilePeerDelayCriticalLimit OBJECT-TYPE
	SYNTAX Gauge
	MAX-ACCESS read-only
	STATUS current
	DESCRIPTION
		"Specifies the critical limit
	    threshold for peer delay."
	::= { ltmDiametersessionProfileEntry 40 }

ltmDiametersessionProfileEgressCriticalMessageRateLimit OBJECT-TYPE
	SYNTAX Gauge
	MAX-ACCESS read-only
	STATUS current
	DESCRIPTION
		"Specifies the
	    critical message rate limit threshold for messages sent to peer."
	::= { ltmDiametersessionProfileEntry 41 }

ltmDiametersessionProfileEgressMajorMessageRateLimit OBJECT-TYPE
	SYNTAX Gauge
	MAX-ACCESS read-only
	STATUS current
	DESCRIPTION
		"Specifies the
	    major message rate limit threshold for messages sent to peer."
	::= { ltmDiametersessionProfileEntry 42 }

ltmDiametersessionProfileIngressCriticalMessageRateLimit OBJECT-TYPE
	SYNTAX Gauge
	MAX-ACCESS read-only
	STATUS current
	DESCRIPTION
		"Specifies the
	    critical message rate limit threshold for messages received from peer."
	::= { ltmDiametersessionProfileEntry 43 }

ltmDiametersessionProfileIngressMajorMessageRateLimit OBJECT-TYPE
	SYNTAX Gauge
	MAX-ACCESS read-only
	STATUS current
	DESCRIPTION
		"Specifies the
	    major message rate limit threshold for messages received peer."
	::= { ltmDiametersessionProfileEntry 44 }

ltmDiametersessionProfileDynamicRouteInsertion OBJECT-TYPE
	SYNTAX INTEGER {
		false(0),
		true(1)
	}
	MAX-ACCESS read-only
	STATUS current
	DESCRIPTION
		"If enabled,
	    dynamically add routes for connected peers."
	::= { ltmDiametersessionProfileEntry 45 }

ltmDiametersessionProfileDynamicRouteLookup OBJECT-TYPE
	SYNTAX INTEGER {
		false(0),
		true(1)
	}
	MAX-ACCESS read-only
	STATUS current
	DESCRIPTION
		"If enabled,
	    route messages based on dynamically added routes."
	::= { ltmDiametersessionProfileEntry 46 }

ltmDiametersessionProfileDynamicRouteTimeout OBJECT-TYPE
	SYNTAX Gauge
	MAX-ACCESS read-only
	STATUS current
	DESCRIPTION
		"Specifies the duration after
	    which dynamic routes will be removed after the releated peer
	    connections are closed."
	::= { ltmDiametersessionProfileEntry 47 }

ltmDiametersessionProfilePeerErrorsMajorThreshold OBJECT-TYPE
	SYNTAX Gauge
	MAX-ACCESS read-only
	STATUS current
	DESCRIPTION
		"Specifies the major limit
	    threshold for peer errors."
	::= { ltmDiametersessionProfileEntry 48 }

ltmDiametersessionProfilePeerTimeoutsMajorThreshold OBJECT-TYPE
	SYNTAX Gauge
	MAX-ACCESS read-only
	STATUS current
	DESCRIPTION
		"Specifies the major limit
	    threshold for peer timeouts."
	::= { ltmDiametersessionProfileEntry 49 }

ltmDiametersessionProfileDisconnectPeerAction OBJECT-TYPE
	SYNTAX Gauge
	MAX-ACCESS read-only
	STATUS current
	DESCRIPTION
		"Specifies the type of action
	    taken when Disconnect Peer Request received from peer.
	       None: Terminates connection on receiving DPR.Connection can be re-established between peer and BIGIP.
	       Disable: When set to Disabled, a node  continues to process persistent and active connections.
	       It can accept new connections only if the connections belong to an existing persistent sessions.
	       Force-offline: When set to Forced Offline, a node allows existing connections to time out, but no new connections are allowed.
	    default value is None."
	::= { ltmDiametersessionProfileEntry 50 }

--==================================================================
-- Profile_diametersession_stat
--==================================================================
ltmDiametersessionProfileStatResetStats OBJECT-TYPE
	SYNTAX INTEGER
	MAX-ACCESS read-write
	STATUS current
	DESCRIPTION
		"The action to reset resettable statistics data in ltmDiametersessionProfileStat.
		 Setting this value to 1 will reset statistics data.
		 Note, some statistics data may not be reset including data that are incremental counters."
	::= { ltmDiametersessionProfileStat 1 }

ltmDiametersessionProfileStatNumber OBJECT-TYPE
	SYNTAX INTEGER
	MAX-ACCESS read-only
	STATUS current
	DESCRIPTION
		"The number of ltmDiametersessionProfileStat entries in the table."
	::= { ltmDiametersessionProfileStat 2 }

ltmDiametersessionProfileStatTable OBJECT-TYPE
	SYNTAX SEQUENCE OF LtmDiametersessionProfileStatEntry
	MAX-ACCESS not-accessible
	STATUS current
	DESCRIPTION
		"A table containing statistic information for diameter session profiles."
	::= { ltmDiametersessionProfileStat 3 }

ltmDiametersessionProfileStatEntry OBJECT-TYPE
	SYNTAX  LtmDiametersessionProfileStatEntry
	MAX-ACCESS not-accessible
	STATUS current
	DESCRIPTION
		"Columns in the ltmDiametersessionProfileStat Table"
	INDEX {
		ltmDiametersessionProfileStatName
	}
	::= { ltmDiametersessionProfileStatTable 1 }

LtmDiametersessionProfileStatEntry ::=
	SEQUENCE {
        	ltmDiametersessionProfileStatName                         LongDisplayString,
        	ltmDiametersessionProfileStatVsName                       LongDisplayString,
        	ltmDiametersessionProfileStatTotCapExcReq                 Counter64,
        	ltmDiametersessionProfileStatTotCapExcAns                 Counter64,
        	ltmDiametersessionProfileStatTotDeviceWatchdogRequests    Counter64,
        	ltmDiametersessionProfileStatTotDeviceWatchdogAnswers     Counter64,
        	ltmDiametersessionProfileStatTotDisconnectPeerRequests    Counter64,
        	ltmDiametersessionProfileStatTotDisconnectPeerAnswers     Counter64,
        	ltmDiametersessionProfileStatTotAccountingRequests        Counter64,
        	ltmDiametersessionProfileStatTotAccountingAnswers         Counter64,
        	ltmDiametersessionProfileStatTotCreditControlRequests     Counter64,
        	ltmDiametersessionProfileStatTotCreditControlAnswers      Counter64,
        	ltmDiametersessionProfileStatTotUserAuthorizationRequests Counter64,
        	ltmDiametersessionProfileStatTotUserAuthorizationAnswers  Counter64,
        	ltmDiametersessionProfileStatTotOtherRequests             Counter64,
        	ltmDiametersessionProfileStatTotOtherAnswers              Counter64,
        	ltmDiametersessionProfileStatTotBadMessages               Counter64,
        	ltmDiametersessionProfileStatTotRejectedUnconfiguredPeers Counter64,
        	ltmDiametersessionProfileStatCurReqQueuedForRetrans       Counter64,
        	ltmDiametersessionProfileStatTotRetransReturnedBusy       Counter64,
        	ltmDiametersessionProfileStatTotRetransReturnedUnavail    Counter64,
        	ltmDiametersessionProfileStatTotRetransReqRetransmitted   Counter64,
        	ltmDiametersessionProfileStatTotRetransmissionTimeout     Counter64,
        	ltmDiametersessionProfileStatTotRetransmissionErrorCode   Counter64,
        	ltmDiametersessionProfileStatTotRetransmissionIrule       Counter64,
        	ltmDiametersessionProfileStatTotRequestReceived           Counter64,
        	ltmDiametersessionProfileStatTotRequestSent               Counter64,
        	ltmDiametersessionProfileStatTotDiscardUnroutable         Counter64,
        	ltmDiametersessionProfileStatTotRespondUnroutable         Counter64,
        	ltmDiametersessionProfileStatAveRequestLatency            Counter64,
        	ltmDiametersessionProfileStatAveAnswerLatency             Counter64,
        	ltmDiametersessionProfileStatAvePeerDelay                 Counter64,
        	ltmDiametersessionProfileStatAveRoundTripTime             Counter64,
        	ltmDiametersessionProfileStatCurTrafficRate               Counter64,
        	ltmDiametersessionProfileStatCurErrorAnswerRatio          Counter64,
        	ltmDiametersessionProfileStatCurTimeoutRatio              Counter64,
        	ltmDiametersessionProfileStatTotResultCodeRcvd1xxx        Counter64,
        	ltmDiametersessionProfileStatTotResultCodeRcvd2xxx        Counter64,
        	ltmDiametersessionProfileStatTotResultCodeRcvd3xxx        Counter64,
        	ltmDiametersessionProfileStatTotResultCodeRcvd4xxx        Counter64,
        	ltmDiametersessionProfileStatTotResultCodeRcvd5xxx        Counter64,
        	ltmDiametersessionProfileStatTotResultCodeSent1xxx        Counter64,
        	ltmDiametersessionProfileStatTotResultCodeSent2xxx        Counter64,
        	ltmDiametersessionProfileStatTotResultCodeSent3xxx        Counter64,
        	ltmDiametersessionProfileStatTotResultCodeSent4xxx        Counter64,
        	ltmDiametersessionProfileStatTotResultCodeSent5xxx        Counter64,
        	ltmDiametersessionProfileStatTotLoopedRequests            Counter64
	}

ltmDiametersessionProfileStatName OBJECT-TYPE
	SYNTAX LongDisplayString
	MAX-ACCESS read-only
	STATUS current
	DESCRIPTION
		"The Name of the diametersession profile."
	::= { ltmDiametersessionProfileStatEntry 1 }

ltmDiametersessionProfileStatVsName OBJECT-TYPE
	SYNTAX LongDisplayString
	MAX-ACCESS read-only
	STATUS current
	DESCRIPTION
		"The Name of the virtual server."
	::= { ltmDiametersessionProfileStatEntry 2 }

ltmDiametersessionProfileStatTotCapExcReq OBJECT-TYPE
	SYNTAX Counter64
	MAX-ACCESS read-only
	STATUS current
	DESCRIPTION
		"Displays the number of Capabilities Exchange Request messages."
	::= { ltmDiametersessionProfileStatEntry 3 }

ltmDiametersessionProfileStatTotCapExcAns OBJECT-TYPE
	SYNTAX Counter64
	MAX-ACCESS read-only
	STATUS current
	DESCRIPTION
		"Displays the number of Capabilities Exchange Answer messages."
	::= { ltmDiametersessionProfileStatEntry 4 }

ltmDiametersessionProfileStatTotDeviceWatchdogRequests OBJECT-TYPE
	SYNTAX Counter64
	MAX-ACCESS read-only
	STATUS current
	DESCRIPTION
		"Displays the number of Device Watchdog Request messages."
	::= { ltmDiametersessionProfileStatEntry 5 }

ltmDiametersessionProfileStatTotDeviceWatchdogAnswers OBJECT-TYPE
	SYNTAX Counter64
	MAX-ACCESS read-only
	STATUS current
	DESCRIPTION
		"Displays the number of Device Watchdog Answers messages."
	::= { ltmDiametersessionProfileStatEntry 6 }

ltmDiametersessionProfileStatTotDisconnectPeerRequests OBJECT-TYPE
	SYNTAX Counter64
	MAX-ACCESS read-only
	STATUS current
	DESCRIPTION
		"Displays the number of Disconnect Peer Request messages."
	::= { ltmDiametersessionProfileStatEntry 7 }

ltmDiametersessionProfileStatTotDisconnectPeerAnswers OBJECT-TYPE
	SYNTAX Counter64
	MAX-ACCESS read-only
	STATUS current
	DESCRIPTION
		"Displays the number of Disconnect Peer Answer messages."
	::= { ltmDiametersessionProfileStatEntry 8 }

ltmDiametersessionProfileStatTotAccountingRequests OBJECT-TYPE
	SYNTAX Counter64
	MAX-ACCESS read-only
	STATUS current
	DESCRIPTION
		"Displays the number of Accounting Request messages."
	::= { ltmDiametersessionProfileStatEntry 9 }

ltmDiametersessionProfileStatTotAccountingAnswers OBJECT-TYPE
	SYNTAX Counter64
	MAX-ACCESS read-only
	STATUS current
	DESCRIPTION
		"Displays the number of Accounting Answers messages."
	::= { ltmDiametersessionProfileStatEntry 10 }

ltmDiametersessionProfileStatTotCreditControlRequests OBJECT-TYPE
	SYNTAX Counter64
	MAX-ACCESS read-only
	STATUS current
	DESCRIPTION
		"Displays the number of Credit Control Request messages."
	::= { ltmDiametersessionProfileStatEntry 11 }

ltmDiametersessionProfileStatTotCreditControlAnswers OBJECT-TYPE
	SYNTAX Counter64
	MAX-ACCESS read-only
	STATUS current
	DESCRIPTION
		"Displays the number of Credit Control Answers messages."
	::= { ltmDiametersessionProfileStatEntry 12 }

ltmDiametersessionProfileStatTotUserAuthorizationRequests OBJECT-TYPE
	SYNTAX Counter64
	MAX-ACCESS read-only
	STATUS current
	DESCRIPTION
		"Displays the number of User Authorization Request messages."
	::= { ltmDiametersessionProfileStatEntry 13 }

ltmDiametersessionProfileStatTotUserAuthorizationAnswers OBJECT-TYPE
	SYNTAX Counter64
	MAX-ACCESS read-only
	STATUS current
	DESCRIPTION
		"Displays the number of User Authorization Answers messages."
	::= { ltmDiametersessionProfileStatEntry 14 }

ltmDiametersessionProfileStatTotOtherRequests OBJECT-TYPE
	SYNTAX Counter64
	MAX-ACCESS read-only
	STATUS current
	DESCRIPTION
		"Displays the number of Other Request messages."
	::= { ltmDiametersessionProfileStatEntry 15 }

ltmDiametersessionProfileStatTotOtherAnswers OBJECT-TYPE
	SYNTAX Counter64
	MAX-ACCESS read-only
	STATUS current
	DESCRIPTION
		"Displays the number of Other Answers messages."
	::= { ltmDiametersessionProfileStatEntry 16 }

ltmDiametersessionProfileStatTotBadMessages OBJECT-TYPE
	SYNTAX Counter64
	MAX-ACCESS read-only
	STATUS current
	DESCRIPTION
		"Displays the number of Bad Messages."
	::= { ltmDiametersessionProfileStatEntry 17 }

ltmDiametersessionProfileStatTotRejectedUnconfiguredPeers OBJECT-TYPE
	SYNTAX Counter64
	MAX-ACCESS read-only
	STATUS current
	DESCRIPTION
		"Displays the number of Messages Rejected for Unconfigured Peers."
	::= { ltmDiametersessionProfileStatEntry 18 }

ltmDiametersessionProfileStatCurReqQueuedForRetrans OBJECT-TYPE
	SYNTAX Counter64
	MAX-ACCESS read-only
	STATUS current
	DESCRIPTION
		"Displays the current number of request messages queued for retransmission."
	::= { ltmDiametersessionProfileStatEntry 19 }

ltmDiametersessionProfileStatTotRetransReturnedBusy OBJECT-TYPE
	SYNTAX Counter64
	MAX-ACCESS read-only
	STATUS current
	DESCRIPTION
		"Displays the total number of requests triggered for retransmission that returned a busy answer."
	::= { ltmDiametersessionProfileStatEntry 20 }

ltmDiametersessionProfileStatTotRetransReturnedUnavail OBJECT-TYPE
	SYNTAX Counter64
	MAX-ACCESS read-only
	STATUS current
	DESCRIPTION
		"Displays the total number of requests triggered for retransmission that returned a unable to deliver answer."
	::= { ltmDiametersessionProfileStatEntry 21 }

ltmDiametersessionProfileStatTotRetransReqRetransmitted OBJECT-TYPE
	SYNTAX Counter64
	MAX-ACCESS read-only
	STATUS current
	DESCRIPTION
		"Displays the total number of requests retransmitted."
	::= { ltmDiametersessionProfileStatEntry 22 }

ltmDiametersessionProfileStatTotRetransmissionTimeout OBJECT-TYPE
	SYNTAX Counter64
	MAX-ACCESS read-only
	STATUS current
	DESCRIPTION
		"Displays the total number of requests triggered for retransmission due to timeout."
	::= { ltmDiametersessionProfileStatEntry 23 }

ltmDiametersessionProfileStatTotRetransmissionErrorCode OBJECT-TYPE
	SYNTAX Counter64
	MAX-ACCESS read-only
	STATUS current
	DESCRIPTION
		"Displays the total number of requests triggered for retransmission due a error code."
	::= { ltmDiametersessionProfileStatEntry 24 }

ltmDiametersessionProfileStatTotRetransmissionIrule OBJECT-TYPE
	SYNTAX Counter64
	MAX-ACCESS read-only
	STATUS current
	DESCRIPTION
		"Displays the total number of requests triggered for retransmission by iRule command."
	::= { ltmDiametersessionProfileStatEntry 25 }

ltmDiametersessionProfileStatTotRequestReceived OBJECT-TYPE
	SYNTAX Counter64
	MAX-ACCESS read-only
	STATUS current
	DESCRIPTION
		"Displays the number of request messages received."
	::= { ltmDiametersessionProfileStatEntry 26 }

ltmDiametersessionProfileStatTotRequestSent OBJECT-TYPE
	SYNTAX Counter64
	MAX-ACCESS read-only
	STATUS current
	DESCRIPTION
		"Displays the number of request messages sent."
	::= { ltmDiametersessionProfileStatEntry 27 }

ltmDiametersessionProfileStatTotDiscardUnroutable OBJECT-TYPE
	SYNTAX Counter64
	MAX-ACCESS read-only
	STATUS current
	DESCRIPTION
		"Displays the number of unroutable request messages dropped automatically."
	::= { ltmDiametersessionProfileStatEntry 28 }

ltmDiametersessionProfileStatTotRespondUnroutable OBJECT-TYPE
	SYNTAX Counter64
	MAX-ACCESS read-only
	STATUS current
	DESCRIPTION
		"Displays the number of unroutable request messages converted to error
	     answer messages automatically."
	::= { ltmDiametersessionProfileStatEntry 29 }

ltmDiametersessionProfileStatAveRequestLatency OBJECT-TYPE
	SYNTAX Counter64
	MAX-ACCESS read-only
	STATUS current
	DESCRIPTION
		"Displays the average L7 processing latency for diameter request messages
	     over the last second (in milliseconds)."
	::= { ltmDiametersessionProfileStatEntry 30 }

ltmDiametersessionProfileStatAveAnswerLatency OBJECT-TYPE
	SYNTAX Counter64
	MAX-ACCESS read-only
	STATUS current
	DESCRIPTION
		"Displays the average L7 processing latency for diameter answer messages
	     over the last second. (in milliseconds)."
	::= { ltmDiametersessionProfileStatEntry 31 }

ltmDiametersessionProfileStatAvePeerDelay OBJECT-TYPE
	SYNTAX Counter64
	MAX-ACCESS read-only
	STATUS current
	DESCRIPTION
		"Displays the average time between forwarding a request message to a peer and
	     receiving the answer message from that peer over the last second (in milliseconds)."
	::= { ltmDiametersessionProfileStatEntry 32 }

ltmDiametersessionProfileStatAveRoundTripTime OBJECT-TYPE
	SYNTAX Counter64
	MAX-ACCESS read-only
	STATUS current
	DESCRIPTION
		"Displays the average time between receiving a request message and
	     forwarding the answer message over the last second (in milliseconds)."
	::= { ltmDiametersessionProfileStatEntry 33 }

ltmDiametersessionProfileStatCurTrafficRate OBJECT-TYPE
	SYNTAX Counter64
	MAX-ACCESS read-only
	STATUS current
	DESCRIPTION
		"Displays the number of requests and responses sent and received over the
	     last second."
	::= { ltmDiametersessionProfileStatEntry 34 }

ltmDiametersessionProfileStatCurErrorAnswerRatio OBJECT-TYPE
	SYNTAX Counter64
	MAX-ACCESS read-only
	STATUS current
	DESCRIPTION
		"Displays the percentage of answer messages received containing an
	     error result code (3000-5999)."
	::= { ltmDiametersessionProfileStatEntry 35 }

ltmDiametersessionProfileStatCurTimeoutRatio OBJECT-TYPE
	SYNTAX Counter64
	MAX-ACCESS read-only
	STATUS current
	DESCRIPTION
		"Displays the percentage of answer messages unanswered."
	::= { ltmDiametersessionProfileStatEntry 36 }

ltmDiametersessionProfileStatTotResultCodeRcvd1xxx OBJECT-TYPE
	SYNTAX Counter64
	MAX-ACCESS read-only
	STATUS current
	DESCRIPTION
		"Displays the number of answer messages received with
	     a response code between 1000-1999."
	::= { ltmDiametersessionProfileStatEntry 37 }

ltmDiametersessionProfileStatTotResultCodeRcvd2xxx OBJECT-TYPE
	SYNTAX Counter64
	MAX-ACCESS read-only
	STATUS current
	DESCRIPTION
		"Displays the number of answer messages received with
	     a response code between 2000-2999."
	::= { ltmDiametersessionProfileStatEntry 38 }

ltmDiametersessionProfileStatTotResultCodeRcvd3xxx OBJECT-TYPE
	SYNTAX Counter64
	MAX-ACCESS read-only
	STATUS current
	DESCRIPTION
		"Displays the number of answer messages received with
	     a response code between 3000-3999."
	::= { ltmDiametersessionProfileStatEntry 39 }

ltmDiametersessionProfileStatTotResultCodeRcvd4xxx OBJECT-TYPE
	SYNTAX Counter64
	MAX-ACCESS read-only
	STATUS current
	DESCRIPTION
		"Displays the number of answer messages received with
	     a response code between 4000-4999."
	::= { ltmDiametersessionProfileStatEntry 40 }

ltmDiametersessionProfileStatTotResultCodeRcvd5xxx OBJECT-TYPE
	SYNTAX Counter64
	MAX-ACCESS read-only
	STATUS current
	DESCRIPTION
		"Displays the number of answer messages received with
	     a response code between 5000-5999."
	::= { ltmDiametersessionProfileStatEntry 41 }

ltmDiametersessionProfileStatTotResultCodeSent1xxx OBJECT-TYPE
	SYNTAX Counter64
	MAX-ACCESS read-only
	STATUS current
	DESCRIPTION
		"Displays the number of answer messages sent with a response
	     code between 1000-1999."
	::= { ltmDiametersessionProfileStatEntry 42 }

ltmDiametersessionProfileStatTotResultCodeSent2xxx OBJECT-TYPE
	SYNTAX Counter64
	MAX-ACCESS read-only
	STATUS current
	DESCRIPTION
		"Displays the number of answer messages sent with a response
	     code between 2000-2999."
	::= { ltmDiametersessionProfileStatEntry 43 }

ltmDiametersessionProfileStatTotResultCodeSent3xxx OBJECT-TYPE
	SYNTAX Counter64
	MAX-ACCESS read-only
	STATUS current
	DESCRIPTION
		"Displays the number of answer messages sent with a response
	     code between 3000-3999."
	::= { ltmDiametersessionProfileStatEntry 44 }

ltmDiametersessionProfileStatTotResultCodeSent4xxx OBJECT-TYPE
	SYNTAX Counter64
	MAX-ACCESS read-only
	STATUS current
	DESCRIPTION
		"Displays the number of answer messages sent with a response
	     code between 4000-4999."
	::= { ltmDiametersessionProfileStatEntry 45 }

ltmDiametersessionProfileStatTotResultCodeSent5xxx OBJECT-TYPE
	SYNTAX Counter64
	MAX-ACCESS read-only
	STATUS current
	DESCRIPTION
		"Displays the number of answer messages sent with a response
	     code between 5000-5999."
	::= { ltmDiametersessionProfileStatEntry 46 }

ltmDiametersessionProfileStatTotLoopedRequests OBJECT-TYPE
	SYNTAX Counter64
	MAX-ACCESS read-only
	STATUS current
	DESCRIPTION
		"Displays the total number of looped messages that have been detected."
	::= { ltmDiametersessionProfileStatEntry 47 }

--==================================================================
-- Profile_diameterrouter
--==================================================================
ltmDiameterrouterProfileNumber OBJECT-TYPE
	SYNTAX INTEGER
	MAX-ACCESS read-only
	STATUS current
	DESCRIPTION
		"The number of ltmDiameterrouterProfile entries in the table."
	::= { ltmDiameterrouterProfile 1 }

ltmDiameterrouterProfileTable OBJECT-TYPE
	SYNTAX SEQUENCE OF LtmDiameterrouterProfileEntry
	MAX-ACCESS not-accessible
	STATUS current
	DESCRIPTION
		"A table containing configuration information for diameter router profiles."
	::= { ltmDiameterrouterProfile 2 }

ltmDiameterrouterProfileEntry OBJECT-TYPE
	SYNTAX  LtmDiameterrouterProfileEntry
	MAX-ACCESS not-accessible
	STATUS current
	DESCRIPTION
		"Columns in the ltmDiameterrouterProfile Table"
	INDEX {
		ltmDiameterrouterProfileName
	}
	::= { ltmDiameterrouterProfileTable 1 }

LtmDiameterrouterProfileEntry ::=
	SEQUENCE {
        	ltmDiameterrouterProfileName                              LongDisplayString,
        	ltmDiameterrouterProfileConfigSource                      INTEGER,
        	ltmDiameterrouterProfileDefaultName                       LongDisplayString,
        	ltmDiameterrouterProfileMirrored                          Counter64,
        	ltmDiameterrouterProfileTrafficGroup                      LongDisplayString,
        	ltmDiameterrouterProfileSupportedApplications             Counter64,
        	ltmDiameterrouterProfileIgnorePeerPort                    Counter64,
        	ltmDiameterrouterProfileMaxPendingMessages                Counter64,
        	ltmDiameterrouterProfileMaxPendingBytes                   Counter64,
        	ltmDiameterrouterProfileHaMsgSweeperInterval              Counter64,
        	ltmDiameterrouterProfilePendingReqSweeperInterval         Counter64,
        	ltmDiameterrouterProfileUseLocalConnection                Counter64,
        	ltmDiameterrouterProfileTransactionTimeout                Counter64,
        	ltmDiameterrouterProfileMaxRetries                        Counter64,
        	ltmDiameterrouterProfileIruleScopeMessage                 INTEGER,
        	ltmDiameterrouterProfilePerPeerStats                      INTEGER,
        	ltmDiameterrouterProfileAssociateClientsideToPmbr         INTEGER
	}

ltmDiameterrouterProfileName OBJECT-TYPE
	SYNTAX LongDisplayString
	MAX-ACCESS read-only
	STATUS current
	DESCRIPTION
		"The Name of the diameterrouter profile."
	::= { ltmDiameterrouterProfileEntry 1 }

ltmDiameterrouterProfileConfigSource OBJECT-TYPE
	SYNTAX INTEGER {
		usercfg(0),
		basecfg(1)
	}
	MAX-ACCESS read-only
	STATUS current
	DESCRIPTION
		"The state that specifies whether this is a base/pre-configured profile
	      or user defined profile."
	::= { ltmDiameterrouterProfileEntry 2 }

ltmDiameterrouterProfileDefaultName OBJECT-TYPE
	SYNTAX LongDisplayString
	MAX-ACCESS read-only
	STATUS current
	DESCRIPTION
		"The name of the profile from which the specified profile derives
	      its attribute default values."
	::= { ltmDiameterrouterProfileEntry 3 }

ltmDiameterrouterProfileMirrored OBJECT-TYPE
	SYNTAX Counter64
	MAX-ACCESS read-only
	STATUS current
	DESCRIPTION
		"Enables mirroring of all incoming connections
	    for all virtual servers using this router instance, and all
	    outgoing connection created by this router instance."
	::= { ltmDiameterrouterProfileEntry 4 }

ltmDiameterrouterProfileTrafficGroup OBJECT-TYPE
	SYNTAX LongDisplayString
	MAX-ACCESS read-only
	STATUS current
	DESCRIPTION
		"The traffic group for the router
	    instance. All virtual servers using this router profile will have
	    the their traffic group replaced by the traffic group of the
	    router profile."
	::= { ltmDiameterrouterProfileEntry 5 }

ltmDiameterrouterProfileSupportedApplications OBJECT-TYPE
	SYNTAX Counter64
	MAX-ACCESS read-only
	STATUS current
	DESCRIPTION
		"List of supported application-ids"
	::= { ltmDiameterrouterProfileEntry 6 }

ltmDiameterrouterProfileIgnorePeerPort OBJECT-TYPE
	SYNTAX Counter64
	MAX-ACCESS read-only
	STATUS current
	DESCRIPTION
		"If set, the remote port on the peers
	    connecting to BIGIP is ignored when searching for an existing
	    connection."
	::= { ltmDiameterrouterProfileEntry 7 }

ltmDiameterrouterProfileMaxPendingMessages OBJECT-TYPE
	SYNTAX Counter64
	MAX-ACCESS read-only
	STATUS current
	DESCRIPTION
		"The maximum number of pending
	    messages that are held while waiting for a connection to a peer to
	    be created. Once reached any additional messages to the peer are
	    flagged as undeliverable and dropped. A default value of 0, uses
	    default value 256."
	::= { ltmDiameterrouterProfileEntry 8 }

ltmDiameterrouterProfileMaxPendingBytes OBJECT-TYPE
	SYNTAX Counter64
	MAX-ACCESS read-only
	STATUS current
	DESCRIPTION
		"The maximum number of bytes
	    contained within pending messages that are held while waiting for
	    a connection to a peer to be created. Once reached any additional
	    messages to the peer are flagged as undeliverable and dropped. A
	    default value of 0, uses default value 32768."
	::= { ltmDiameterrouterProfileEntry 9 }

ltmDiameterrouterProfileHaMsgSweeperInterval OBJECT-TYPE
	SYNTAX Counter64
	MAX-ACCESS read-only
	STATUS current
	DESCRIPTION
		"This attribute sets the
	    frequency of the mirrored message sweeper. For virtual servers
	    where mirroring is enabled, the received messages will be
	    processed on both the active device and the standby device. On the
	    standby device, the messages are not routed, instead they are
	    stored in a message store until the active device sends a
	    notification that the message has been routed to the standby
	    device so that the standby device can deliver the message to the
	    equivalent connection for egress processing. A sweeper has been
	    implemented to drop messages from the message store if they remain
	    in the store longer than the time specified in this attribute. The
	    time shall be in milliseconds."
	::= { ltmDiameterrouterProfileEntry 10 }

ltmDiameterrouterProfilePendingReqSweeperInterval OBJECT-TYPE
	SYNTAX Counter64
	MAX-ACCESS read-only
	STATUS current
	DESCRIPTION
		"This attribute sets the
	    frequency for the pending request sweeper. When run, data retained
	    to assist with forwarding received answer messages will be removed
	    if it is older than twice the transaction timeout value. If set to
	    zero the sweeper will be disabled. The time shall be in
	    milli-seconds."
	::= { ltmDiameterrouterProfileEntry 11 }

ltmDiameterrouterProfileUseLocalConnection OBJECT-TYPE
	SYNTAX Counter64
	MAX-ACCESS read-only
	STATUS current
	DESCRIPTION
		"Controls whether connections
	    established by the ingress TMM are preferred over connections
	    established by other TMMs when selecting egress connection to
	    destination peer."
	::= { ltmDiameterrouterProfileEntry 12 }

ltmDiameterrouterProfileTransactionTimeout OBJECT-TYPE
	SYNTAX Counter64
	MAX-ACCESS read-only
	STATUS current
	DESCRIPTION
		"Specifies the maximum time in
	    seconds between request and its response. A provisional response
	    restarts the timer. This may not affect all transactions. The
	    scenarios where BIG-IP waits for response, is impacted, by
	    dropping any persistent data maintained for this request."
	::= { ltmDiameterrouterProfileEntry 13 }

ltmDiameterrouterProfileMaxRetries OBJECT-TYPE
	SYNTAX Counter64
	MAX-ACCESS read-only
	STATUS current
	DESCRIPTION
		"The maximum number of attempts to retry
	    creating a connection to a peer. Once reached, all pending
	    messages will be flagged as undeliverable and returned to the
	    originator. A default value of 0, indicates no connection retries
	    will happen.  Need to remove this from schema, never exposed to
	    end user."
	::= { ltmDiameterrouterProfileEntry 14 }

ltmDiameterrouterProfileIruleScopeMessage OBJECT-TYPE
	SYNTAX INTEGER {
		false(0),
		true(1)
	}
	MAX-ACCESS read-only
	STATUS current
	DESCRIPTION
		"An attribute in a
	    MR (message-routing) diameter router profile that causes Diameter
	    iRule events to be processed in the scope of the executing
	    message, rather than one by one in the scope of the connection. If
	    true, each message has its own Tcl execution context and local
	    variables, and may execute iRules concurrently with other
	    messages. Otherwise all messages on a connection flow share a
	    single execution context and share their local variables, so must
	    queue to execute one by one. This is false by default (the legacy
	    mode). Before setting this to true, some pre-existing iRules might
	    need to be adjusted to avoid sharing local variables."
	::= { ltmDiameterrouterProfileEntry 15 }

ltmDiameterrouterProfilePerPeerStats OBJECT-TYPE
	SYNTAX INTEGER {
		false(0),
		true(1)
	}
	MAX-ACCESS read-only
	STATUS current
	DESCRIPTION
		"If set to true, the profile specific statistics
	    will be captured for each pool member. The default value is false."
	::= { ltmDiameterrouterProfileEntry 16 }

ltmDiameterrouterProfileAssociateClientsideToPmbr OBJECT-TYPE
	SYNTAX INTEGER {
		false(0),
		true(1)
	}
	MAX-ACCESS read-only
	STATUS current
	DESCRIPTION
		"If set to true, the configured
	    routes will be scanned for a pool member that matches a new clientside
	    connection. If found, the clientside connection will be associated with
	    the pool member allowing the activity on the clientside connection to be
	    included with the activity of the pool member. The default value is
	    false."
	::= { ltmDiameterrouterProfileEntry 17 }

--==================================================================
-- Profile_diameterrouter_stat
--==================================================================
ltmDiameterrouterProfileStatResetStats OBJECT-TYPE
	SYNTAX INTEGER
	MAX-ACCESS read-write
	STATUS current
	DESCRIPTION
		"The action to reset resettable statistics data in ltmDiameterrouterProfileStat.
		 Setting this value to 1 will reset statistics data.
		 Note, some statistics data may not be reset including data that are incremental counters."
	::= { ltmDiameterrouterProfileStat 1 }

ltmDiameterrouterProfileStatNumber OBJECT-TYPE
	SYNTAX INTEGER
	MAX-ACCESS read-only
	STATUS current
	DESCRIPTION
		"The number of ltmDiameterrouterProfileStat entries in the table."
	::= { ltmDiameterrouterProfileStat 2 }

ltmDiameterrouterProfileStatTable OBJECT-TYPE
	SYNTAX SEQUENCE OF LtmDiameterrouterProfileStatEntry
	MAX-ACCESS not-accessible
	STATUS current
	DESCRIPTION
		"A table containing statistic information for diameter router profiles."
	::= { ltmDiameterrouterProfileStat 3 }

ltmDiameterrouterProfileStatEntry OBJECT-TYPE
	SYNTAX  LtmDiameterrouterProfileStatEntry
	MAX-ACCESS not-accessible
	STATUS current
	DESCRIPTION
		"Columns in the ltmDiameterrouterProfileStat Table"
	INDEX {
		ltmDiameterrouterProfileStatName
	}
	::= { ltmDiameterrouterProfileStatTable 1 }

LtmDiameterrouterProfileStatEntry ::=
	SEQUENCE {
        	ltmDiameterrouterProfileStatName                          LongDisplayString,
        	ltmDiameterrouterProfileStatVsName                        LongDisplayString,
        	ltmDiameterrouterProfileStatTotMessgesIn                  Counter64,
        	ltmDiameterrouterProfileStatTotMessagesInRetry            Counter64,
        	ltmDiameterrouterProfileStatTotMessagesOut                Counter64,
        	ltmDiameterrouterProfileStatTotMessagesCannotReturn       Counter64,
        	ltmDiameterrouterProfileStatTotMessagesRouted             Counter64,
        	ltmDiameterrouterProfileStatTotMessagesUnroutable         Counter64,
        	ltmDiameterrouterProfileStatTotMessagesDropped            Counter64,
        	ltmDiameterrouterProfileStatTotMessagesQueueFull          Counter64,
        	ltmDiameterrouterProfileStatTotMessagesNoConnection       Counter64,
        	ltmDiameterrouterProfileStatTotMessagesConnectionClosed   Counter64,
        	ltmDiameterrouterProfileStatTotMessagesInternalError      Counter64,
        	ltmDiameterrouterProfileStatTotMessagesPersistInUse       Counter64,
        	ltmDiameterrouterProfileStatTotMessagesStandbyDropped     Counter64,
        	ltmDiameterrouterProfileStatTotMessagesMaxRetries         Counter64,
        	ltmDiameterrouterProfileStatTotMessagesInCloned           Counter64,
        	ltmDiameterrouterProfileStatTotMessagesReturned           Counter64,
        	ltmDiameterrouterProfileStatTotPayloadBytesIn             Counter64,
        	ltmDiameterrouterProfileStatTotPayloadBytesOut            Counter64,
        	ltmDiameterrouterProfileStatCurIncomingStreams            Counter64,
        	ltmDiameterrouterProfileStatCurOutgoingStreams            Counter64,
        	ltmDiameterrouterProfileStatTotIncomingStreams            Counter64,
        	ltmDiameterrouterProfileStatTotOutgoingStreams            Counter64,
        	ltmDiameterrouterProfileStatTotFailedOutgoingStreams      Counter64,
        	ltmDiameterrouterProfileStatCurIncomingConnections        Counter64,
        	ltmDiameterrouterProfileStatCurOutgoingConnections        Counter64,
        	ltmDiameterrouterProfileStatCurAutoInitOutgoingConns      Counter64,
        	ltmDiameterrouterProfileStatTotIncomingConnections        Counter64,
        	ltmDiameterrouterProfileStatTotOutgoingConnections        Counter64,
        	ltmDiameterrouterProfileStatTotAutoInitOutgoingConns      Counter64,
        	ltmDiameterrouterProfileStatTotFailedOutgoingConnections  Counter64,
        	ltmDiameterrouterProfileStatTotFailAutoInitOutgoingConns  Counter64,
        	ltmDiameterrouterProfileStatCurPassthruConnections        Counter64,
        	ltmDiameterrouterProfileStatTotPassthruConnections        Counter64,
        	ltmDiameterrouterProfileStatTotFailedPassthruConnections  Counter64,
        	ltmDiameterrouterProfileStatTotPassthruBytes              Counter64,
        	ltmDiameterrouterProfileStatCurPendingRequests            Gauge,
        	ltmDiameterrouterProfileStatTotExpiredPendingRequests     Gauge,
        	ltmDiameterrouterProfileStatTotDroppedUnexpectedAnswers   Gauge,
        	ltmDiameterrouterProfileStatTotDroppedLateAnswers         Gauge,
        	ltmDiameterrouterProfileStatCurDynamicRoutes              Gauge
	}

ltmDiameterrouterProfileStatName OBJECT-TYPE
	SYNTAX LongDisplayString
	MAX-ACCESS read-only
	STATUS current
	DESCRIPTION
		"The Name of the diameterrouter profile."
	::= { ltmDiameterrouterProfileStatEntry 1 }

ltmDiameterrouterProfileStatVsName OBJECT-TYPE
	SYNTAX LongDisplayString
	MAX-ACCESS read-only
	STATUS current
	DESCRIPTION
		"The Name of the virtual server."
	::= { ltmDiameterrouterProfileStatEntry 2 }

ltmDiameterrouterProfileStatTotMessgesIn OBJECT-TYPE
	SYNTAX Counter64
	MAX-ACCESS read-only
	STATUS current
	DESCRIPTION
		"Displays the number of messages received for forwarding."
	::= { ltmDiameterrouterProfileStatEntry 3 }

ltmDiameterrouterProfileStatTotMessagesInRetry OBJECT-TYPE
	SYNTAX Counter64
	MAX-ACCESS read-only
	STATUS current
	DESCRIPTION
		"Displays the number of retry messages received for forwarding."
	::= { ltmDiameterrouterProfileStatEntry 4 }

ltmDiameterrouterProfileStatTotMessagesOut OBJECT-TYPE
	SYNTAX Counter64
	MAX-ACCESS read-only
	STATUS current
	DESCRIPTION
		"Displays the number of messages forwarded or returned to the originator."
	::= { ltmDiameterrouterProfileStatEntry 5 }

ltmDiameterrouterProfileStatTotMessagesCannotReturn OBJECT-TYPE
	SYNTAX Counter64
	MAX-ACCESS read-only
	STATUS current
	DESCRIPTION
		"Displays the number of messages which routing failed and could not be returned to the originator."
	::= { ltmDiameterrouterProfileStatEntry 6 }

ltmDiameterrouterProfileStatTotMessagesRouted OBJECT-TYPE
	SYNTAX Counter64
	MAX-ACCESS read-only
	STATUS current
	DESCRIPTION
		"Displays the number of messages where a route was successfully found."
	::= { ltmDiameterrouterProfileStatEntry 7 }

ltmDiameterrouterProfileStatTotMessagesUnroutable OBJECT-TYPE
	SYNTAX Counter64
	MAX-ACCESS read-only
	STATUS current
	DESCRIPTION
		"Displays the number of messages where no route was found."
	::= { ltmDiameterrouterProfileStatEntry 8 }

ltmDiameterrouterProfileStatTotMessagesDropped OBJECT-TYPE
	SYNTAX Counter64
	MAX-ACCESS read-only
	STATUS current
	DESCRIPTION
		"Displays the number of messages dropped via an iRule."
	::= { ltmDiameterrouterProfileStatEntry 9 }

ltmDiameterrouterProfileStatTotMessagesQueueFull OBJECT-TYPE
	SYNTAX Counter64
	MAX-ACCESS read-only
	STATUS current
	DESCRIPTION
		"Displays the number of messages which were routed but the outgoing
	      queue for the destination was full."
	::= { ltmDiameterrouterProfileStatEntry 10 }

ltmDiameterrouterProfileStatTotMessagesNoConnection OBJECT-TYPE
	SYNTAX Counter64
	MAX-ACCESS read-only
	STATUS current
	DESCRIPTION
		"Displays the number of messages which were routed to a connection which was closed before the
	      message could be delivered."
	::= { ltmDiameterrouterProfileStatEntry 11 }

ltmDiameterrouterProfileStatTotMessagesConnectionClosed OBJECT-TYPE
	SYNTAX Counter64
	MAX-ACCESS read-only
	STATUS current
	DESCRIPTION
		"Displays the number of messages which were pending delivery when the connection closed."
	::= { ltmDiameterrouterProfileStatEntry 12 }

ltmDiameterrouterProfileStatTotMessagesInternalError OBJECT-TYPE
	SYNTAX Counter64
	MAX-ACCESS read-only
	STATUS current
	DESCRIPTION
		"Displays the number of messages which were not routed due to an internal error ."
	::= { ltmDiameterrouterProfileStatEntry 13 }

ltmDiameterrouterProfileStatTotMessagesPersistInUse OBJECT-TYPE
	SYNTAX Counter64
	MAX-ACCESS read-only
	STATUS current
	DESCRIPTION
		"Displays the number of messages which after routing failed to add a persistence entry because it
	      was already in use."
	::= { ltmDiameterrouterProfileStatEntry 14 }

ltmDiameterrouterProfileStatTotMessagesStandbyDropped OBJECT-TYPE
	SYNTAX Counter64
	MAX-ACCESS read-only
	STATUS current
	DESCRIPTION
		"Displays the number of messages which were dropped on the
	      standby device."
	::= { ltmDiameterrouterProfileStatEntry 15 }

ltmDiameterrouterProfileStatTotMessagesMaxRetries OBJECT-TYPE
	SYNTAX Counter64
	MAX-ACCESS read-only
	STATUS current
	DESCRIPTION
		"Displays the number of messages returned to the originator because the latest attempt to retry
	      routing exceeded the configured max retry count."
	::= { ltmDiameterrouterProfileStatEntry 16 }

ltmDiameterrouterProfileStatTotMessagesInCloned OBJECT-TYPE
	SYNTAX Counter64
	MAX-ACCESS read-only
	STATUS current
	DESCRIPTION
		"Displays the total number of messages cloned per route."
	::= { ltmDiameterrouterProfileStatEntry 17 }

ltmDiameterrouterProfileStatTotMessagesReturned OBJECT-TYPE
	SYNTAX Counter64
	MAX-ACCESS read-only
	STATUS current
	DESCRIPTION
		"Displays the number of messages returned."
	::= { ltmDiameterrouterProfileStatEntry 18 }

ltmDiameterrouterProfileStatTotPayloadBytesIn OBJECT-TYPE
	SYNTAX Counter64
	MAX-ACCESS read-only
	STATUS current
	DESCRIPTION
		"Displays the number of bytes of payload received."
	::= { ltmDiameterrouterProfileStatEntry 19 }

ltmDiameterrouterProfileStatTotPayloadBytesOut OBJECT-TYPE
	SYNTAX Counter64
	MAX-ACCESS read-only
	STATUS current
	DESCRIPTION
		"Displays the number of bytes of payload sent."
	::= { ltmDiameterrouterProfileStatEntry 20 }

ltmDiameterrouterProfileStatCurIncomingStreams OBJECT-TYPE
	SYNTAX Counter64
	MAX-ACCESS read-only
	STATUS current
	DESCRIPTION
		"Displays the number of active incoming streams."
	::= { ltmDiameterrouterProfileStatEntry 21 }

ltmDiameterrouterProfileStatCurOutgoingStreams OBJECT-TYPE
	SYNTAX Counter64
	MAX-ACCESS read-only
	STATUS current
	DESCRIPTION
		"Displays the number of active outgoing streams."
	::= { ltmDiameterrouterProfileStatEntry 22 }

ltmDiameterrouterProfileStatTotIncomingStreams OBJECT-TYPE
	SYNTAX Counter64
	MAX-ACCESS read-only
	STATUS current
	DESCRIPTION
		"Displays the total number of incoming streams since TMM restart or stats reset."
	::= { ltmDiameterrouterProfileStatEntry 23 }

ltmDiameterrouterProfileStatTotOutgoingStreams OBJECT-TYPE
	SYNTAX Counter64
	MAX-ACCESS read-only
	STATUS current
	DESCRIPTION
		"Displays the total number of outgoing streams since TMM restart or stats reset."
	::= { ltmDiameterrouterProfileStatEntry 24 }

ltmDiameterrouterProfileStatTotFailedOutgoingStreams OBJECT-TYPE
	SYNTAX Counter64
	MAX-ACCESS read-only
	STATUS current
	DESCRIPTION
		"Displays the total number of failed outgoing streams since TMM restart or stats reset."
	::= { ltmDiameterrouterProfileStatEntry 25 }

ltmDiameterrouterProfileStatCurIncomingConnections OBJECT-TYPE
	SYNTAX Counter64
	MAX-ACCESS read-only
	STATUS current
	DESCRIPTION
		"Displays the number of active incoming connections."
	::= { ltmDiameterrouterProfileStatEntry 26 }

ltmDiameterrouterProfileStatCurOutgoingConnections OBJECT-TYPE
	SYNTAX Counter64
	MAX-ACCESS read-only
	STATUS current
	DESCRIPTION
		"Displays the number of active outgoing connections (including outgoing connections created by
	      auto-initialization)."
	::= { ltmDiameterrouterProfileStatEntry 27 }

ltmDiameterrouterProfileStatCurAutoInitOutgoingConns OBJECT-TYPE
	SYNTAX Counter64
	MAX-ACCESS read-only
	STATUS current
	DESCRIPTION
		"Displays the number of active outgoing connections created by auto-initialization."
	::= { ltmDiameterrouterProfileStatEntry 28 }

ltmDiameterrouterProfileStatTotIncomingConnections OBJECT-TYPE
	SYNTAX Counter64
	MAX-ACCESS read-only
	STATUS current
	DESCRIPTION
		"Displays the total number of incoming connections created since TMM restart or stats reset."
	::= { ltmDiameterrouterProfileStatEntry 29 }

ltmDiameterrouterProfileStatTotOutgoingConnections OBJECT-TYPE
	SYNTAX Counter64
	MAX-ACCESS read-only
	STATUS current
	DESCRIPTION
		"Displays the total number of outgoing connections created since TMM restart or stats reset
	      (including outgoing connections created by auto-initialization)."
	::= { ltmDiameterrouterProfileStatEntry 30 }

ltmDiameterrouterProfileStatTotAutoInitOutgoingConns OBJECT-TYPE
	SYNTAX Counter64
	MAX-ACCESS read-only
	STATUS current
	DESCRIPTION
		"Displays the total number of outgoing connections created by auto-initialization since
	      TMM restart or stats reset."
	::= { ltmDiameterrouterProfileStatEntry 31 }

ltmDiameterrouterProfileStatTotFailedOutgoingConnections OBJECT-TYPE
	SYNTAX Counter64
	MAX-ACCESS read-only
	STATUS current
	DESCRIPTION
		"Displays the total number of outgoing connections that failed to be established."
	::= { ltmDiameterrouterProfileStatEntry 32 }

ltmDiameterrouterProfileStatTotFailAutoInitOutgoingConns OBJECT-TYPE
	SYNTAX Counter64
	MAX-ACCESS read-only
	STATUS current
	DESCRIPTION
		"Displays the total number of outgoing connections that failed to be established by
	      auto-initalization."
	::= { ltmDiameterrouterProfileStatEntry 33 }

ltmDiameterrouterProfileStatCurPassthruConnections OBJECT-TYPE
	SYNTAX Counter64
	MAX-ACCESS read-only
	STATUS current
	DESCRIPTION
		"Displays the number of active pass through connections."
	::= { ltmDiameterrouterProfileStatEntry 34 }

ltmDiameterrouterProfileStatTotPassthruConnections OBJECT-TYPE
	SYNTAX Counter64
	MAX-ACCESS read-only
	STATUS current
	DESCRIPTION
		"Displays the total number of pass through connections since TMM restart or stats reset."
	::= { ltmDiameterrouterProfileStatEntry 35 }

ltmDiameterrouterProfileStatTotFailedPassthruConnections OBJECT-TYPE
	SYNTAX Counter64
	MAX-ACCESS read-only
	STATUS current
	DESCRIPTION
		"Displays the total number of failed pass through connections since TMM restart or stats reset."
	::= { ltmDiameterrouterProfileStatEntry 36 }

ltmDiameterrouterProfileStatTotPassthruBytes OBJECT-TYPE
	SYNTAX Counter64
	MAX-ACCESS read-only
	STATUS current
	DESCRIPTION
		"Displays the number of pass through bytes."
	::= { ltmDiameterrouterProfileStatEntry 37 }

ltmDiameterrouterProfileStatCurPendingRequests OBJECT-TYPE
	SYNTAX Gauge
	MAX-ACCESS read-only
	STATUS current
	DESCRIPTION
		"Displays the cur_pending_requests"
	::= { ltmDiameterrouterProfileStatEntry 38 }

ltmDiameterrouterProfileStatTotExpiredPendingRequests OBJECT-TYPE
	SYNTAX Gauge
	MAX-ACCESS read-only
	STATUS current
	DESCRIPTION
		"Displays the tot_expired_pending_requests"
	::= { ltmDiameterrouterProfileStatEntry 39 }

ltmDiameterrouterProfileStatTotDroppedUnexpectedAnswers OBJECT-TYPE
	SYNTAX Gauge
	MAX-ACCESS read-only
	STATUS current
	DESCRIPTION
		"Displays the tot_dropped_unexpected_answers"
	::= { ltmDiameterrouterProfileStatEntry 40 }

ltmDiameterrouterProfileStatTotDroppedLateAnswers OBJECT-TYPE
	SYNTAX Gauge
	MAX-ACCESS read-only
	STATUS current
	DESCRIPTION
		"Displays the tot_dropped_late_answers"
	::= { ltmDiameterrouterProfileStatEntry 41 }

ltmDiameterrouterProfileStatCurDynamicRoutes OBJECT-TYPE
	SYNTAX Gauge
	MAX-ACCESS read-only
	STATUS current
	DESCRIPTION
		"Quantity of dynamic routes that are currently active"
	::= { ltmDiameterrouterProfileStatEntry 42 }

--==================================================================
-- Mr_pmbr_diameter_session_stat
--==================================================================
ltmMrPmbrDiameterSessionStatResetStats OBJECT-TYPE
	SYNTAX INTEGER
	MAX-ACCESS read-write
	STATUS current
	DESCRIPTION
		"The action to reset resettable statistics data in ltmMrPmbrDiameterSessionStat.
		 Setting this value to 1 will reset statistics data.
		 Note, some statistics data may not be reset including data that are incremental counters."
	::= { ltmMrPmbrDiameterSessionStat 1 }

ltmMrPmbrDiameterSessionStatNumber OBJECT-TYPE
	SYNTAX INTEGER
	MAX-ACCESS read-only
	STATUS current
	DESCRIPTION
		"The number of ltmMrPmbrDiameterSessionStat entries in the table."
	::= { ltmMrPmbrDiameterSessionStat 2 }

ltmMrPmbrDiameterSessionStatTable OBJECT-TYPE
	SYNTAX SEQUENCE OF LtmMrPmbrDiameterSessionStatEntry
	MAX-ACCESS not-accessible
	STATUS current
	DESCRIPTION
		"A table containing statistic information for message routing diameter session profiles."
	::= { ltmMrPmbrDiameterSessionStat 3 }

ltmMrPmbrDiameterSessionStatEntry OBJECT-TYPE
	SYNTAX  LtmMrPmbrDiameterSessionStatEntry
	MAX-ACCESS not-accessible
	STATUS current
	DESCRIPTION
		"Columns in the ltmMrPmbrDiameterSessionStat Table"
	INDEX {
		ltmMrPmbrDiameterSessionStatRouterInst,
		ltmMrPmbrDiameterSessionStatMrType,
		ltmMrPmbrDiameterSessionStatTrName,
		ltmMrPmbrDiameterSessionStatPool,
		ltmMrPmbrDiameterSessionStatAddrType,
		ltmMrPmbrDiameterSessionStatAddr,
		ltmMrPmbrDiameterSessionStatProfileName,
		ltmMrPmbrDiameterSessionStatPort
	}
	::= { ltmMrPmbrDiameterSessionStatTable 1 }

LtmMrPmbrDiameterSessionStatEntry ::=
	SEQUENCE {
        	ltmMrPmbrDiameterSessionStatRouterInst                    LongDisplayString,
        	ltmMrPmbrDiameterSessionStatMrType                        LongDisplayString,
        	ltmMrPmbrDiameterSessionStatTrName                        LongDisplayString,
        	ltmMrPmbrDiameterSessionStatPool                          LongDisplayString,
        	ltmMrPmbrDiameterSessionStatAddrType                      InetAddressType,
        	ltmMrPmbrDiameterSessionStatAddr                          InetAddress,
        	ltmMrPmbrDiameterSessionStatProfileName                   LongDisplayString,
        	ltmMrPmbrDiameterSessionStatPort                          InetPortNumber,
        	ltmMrPmbrDiameterSessionStatTotCapExcReq                  Counter64,
        	ltmMrPmbrDiameterSessionStatTotCapExcAns                  Counter64,
        	ltmMrPmbrDiameterSessionStatTotDeviceWatchdogRequests     Counter64,
        	ltmMrPmbrDiameterSessionStatTotDeviceWatchdogAnswers      Counter64,
        	ltmMrPmbrDiameterSessionStatTotDisconnectPeerRequests     Counter64,
        	ltmMrPmbrDiameterSessionStatTotDisconnectPeerAnswers      Counter64,
        	ltmMrPmbrDiameterSessionStatTotAccountingRequests         Counter64,
        	ltmMrPmbrDiameterSessionStatTotAccountingAnswers          Counter64,
        	ltmMrPmbrDiameterSessionStatTotCreditControlRequests      Counter64,
        	ltmMrPmbrDiameterSessionStatTotCreditControlAnswers       Counter64,
        	ltmMrPmbrDiameterSessionStatTotUserAuthorizationRequests  Counter64,
        	ltmMrPmbrDiameterSessionStatTotUserAuthorizationAnswers   Counter64,
        	ltmMrPmbrDiameterSessionStatTotOtherRequests              Counter64,
        	ltmMrPmbrDiameterSessionStatTotOtherAnswers               Counter64,
        	ltmMrPmbrDiameterSessionStatTotBadMessages                Counter64,
        	ltmMrPmbrDiameterSessionStatTotRejectedUnconfiguredPeers  Counter64,
        	ltmMrPmbrDiameterSessionStatCurReqQueuedForRetrans        Counter64,
        	ltmMrPmbrDiameterSessionStatTotRetransReturnedBusy        Counter64,
        	ltmMrPmbrDiameterSessionStatTotRetransReturnedUnavail     Counter64,
        	ltmMrPmbrDiameterSessionStatTotRetransReqRetransmit       Counter64,
        	ltmMrPmbrDiameterSessionStatTotRetransmissionTimeout      Counter64,
        	ltmMrPmbrDiameterSessionStatTotRetransmissionErrorCode    Counter64,
        	ltmMrPmbrDiameterSessionStatTotRetransmissionIrule        Counter64,
        	ltmMrPmbrDiameterSessionStatTotRequestReceived            Counter64,
        	ltmMrPmbrDiameterSessionStatTotRequestSent                Counter64,
        	ltmMrPmbrDiameterSessionStatTotDiscardUnroutable          Counter64,
        	ltmMrPmbrDiameterSessionStatTotRespondUnroutable          Counter64,
        	ltmMrPmbrDiameterSessionStatAveRequestLatency             Counter64,
        	ltmMrPmbrDiameterSessionStatAveAnswerLatency              Counter64,
        	ltmMrPmbrDiameterSessionStatAvePeerDelay                  Counter64,
        	ltmMrPmbrDiameterSessionStatAveRoundTripTime              Counter64,
        	ltmMrPmbrDiameterSessionStatCurTrafficRate                Counter64,
        	ltmMrPmbrDiameterSessionStatCurTimeoutRatio               Counter64,
        	ltmMrPmbrDiameterSessionStatCurErrorAnswerRatio           Counter64,
        	ltmMrPmbrDiameterSessionStatTotResultCodeRcvd1xxx         Counter64,
        	ltmMrPmbrDiameterSessionStatTotResultCodeRcvd2xxx         Counter64,
        	ltmMrPmbrDiameterSessionStatTotResultCodeRcvd3xxx         Counter64,
        	ltmMrPmbrDiameterSessionStatTotResultCodeRcvd4xxx         Counter64,
        	ltmMrPmbrDiameterSessionStatTotResultCodeRcvd5xxx         Counter64,
        	ltmMrPmbrDiameterSessionStatTotResultCodeSent1xxx         Counter64,
        	ltmMrPmbrDiameterSessionStatTotResultCodeSent2xxx         Counter64,
        	ltmMrPmbrDiameterSessionStatTotResultCodeSent3xxx         Counter64,
        	ltmMrPmbrDiameterSessionStatTotResultCodeSent4xxx         Counter64,
        	ltmMrPmbrDiameterSessionStatTotResultCodeSent5xxx         Counter64
	}

ltmMrPmbrDiameterSessionStatRouterInst OBJECT-TYPE
	SYNTAX LongDisplayString
	MAX-ACCESS read-only
	STATUS current
	DESCRIPTION
		"The name of the router instance."
	::= { ltmMrPmbrDiameterSessionStatEntry 1 }

ltmMrPmbrDiameterSessionStatMrType OBJECT-TYPE
	SYNTAX LongDisplayString
	MAX-ACCESS read-only
	STATUS current
	DESCRIPTION
		"The type of transport - config or virtual."
	::= { ltmMrPmbrDiameterSessionStatEntry 2 }

ltmMrPmbrDiameterSessionStatTrName OBJECT-TYPE
	SYNTAX LongDisplayString
	MAX-ACCESS read-only
	STATUS current
	DESCRIPTION
		"The name of the transport config."
	::= { ltmMrPmbrDiameterSessionStatEntry 3 }

ltmMrPmbrDiameterSessionStatPool OBJECT-TYPE
	SYNTAX LongDisplayString
	MAX-ACCESS read-only
	STATUS current
	DESCRIPTION
		"The name of the pool."
	::= { ltmMrPmbrDiameterSessionStatEntry 4 }

ltmMrPmbrDiameterSessionStatAddrType OBJECT-TYPE
	SYNTAX InetAddressType
	MAX-ACCESS read-only
	STATUS current
	DESCRIPTION
		"The IP address type of the pool member address."
	::= { ltmMrPmbrDiameterSessionStatEntry 5 }

ltmMrPmbrDiameterSessionStatAddr OBJECT-TYPE
	SYNTAX InetAddress
	MAX-ACCESS read-only
	STATUS current
	DESCRIPTION
		"The IP address of the pool member"
	::= { ltmMrPmbrDiameterSessionStatEntry 6 }

ltmMrPmbrDiameterSessionStatProfileName OBJECT-TYPE
	SYNTAX LongDisplayString
	MAX-ACCESS read-only
	STATUS current
	DESCRIPTION
		"The name of the diameter session profile."
	::= { ltmMrPmbrDiameterSessionStatEntry 7 }

ltmMrPmbrDiameterSessionStatPort OBJECT-TYPE
	SYNTAX InetPortNumber
	MAX-ACCESS read-only
	STATUS current
	DESCRIPTION
		"The port number of the specified pool member."
	::= { ltmMrPmbrDiameterSessionStatEntry 8 }

ltmMrPmbrDiameterSessionStatTotCapExcReq OBJECT-TYPE
	SYNTAX Counter64
	MAX-ACCESS read-only
	STATUS current
	DESCRIPTION
		"Displays the number of Capabilities Exchange Request messages."
	::= { ltmMrPmbrDiameterSessionStatEntry 9 }

ltmMrPmbrDiameterSessionStatTotCapExcAns OBJECT-TYPE
	SYNTAX Counter64
	MAX-ACCESS read-only
	STATUS current
	DESCRIPTION
		"Displays the number of Capabilities Exchange Answer messages."
	::= { ltmMrPmbrDiameterSessionStatEntry 10 }

ltmMrPmbrDiameterSessionStatTotDeviceWatchdogRequests OBJECT-TYPE
	SYNTAX Counter64
	MAX-ACCESS read-only
	STATUS current
	DESCRIPTION
		"Displays the number of Device Watchdog Request messages."
	::= { ltmMrPmbrDiameterSessionStatEntry 11 }

ltmMrPmbrDiameterSessionStatTotDeviceWatchdogAnswers OBJECT-TYPE
	SYNTAX Counter64
	MAX-ACCESS read-only
	STATUS current
	DESCRIPTION
		"Displays the number of Device Watchdog Answers messages."
	::= { ltmMrPmbrDiameterSessionStatEntry 12 }

ltmMrPmbrDiameterSessionStatTotDisconnectPeerRequests OBJECT-TYPE
	SYNTAX Counter64
	MAX-ACCESS read-only
	STATUS current
	DESCRIPTION
		"Displays the number of Disconnect Peer Request messages."
	::= { ltmMrPmbrDiameterSessionStatEntry 13 }

ltmMrPmbrDiameterSessionStatTotDisconnectPeerAnswers OBJECT-TYPE
	SYNTAX Counter64
	MAX-ACCESS read-only
	STATUS current
	DESCRIPTION
		"Displays the number of Disconnect Peer Answer messages."
	::= { ltmMrPmbrDiameterSessionStatEntry 14 }

ltmMrPmbrDiameterSessionStatTotAccountingRequests OBJECT-TYPE
	SYNTAX Counter64
	MAX-ACCESS read-only
	STATUS current
	DESCRIPTION
		"Displays the number of Accounting Request messages."
	::= { ltmMrPmbrDiameterSessionStatEntry 15 }

ltmMrPmbrDiameterSessionStatTotAccountingAnswers OBJECT-TYPE
	SYNTAX Counter64
	MAX-ACCESS read-only
	STATUS current
	DESCRIPTION
		"Displays the number of Accounting Answers messages."
	::= { ltmMrPmbrDiameterSessionStatEntry 16 }

ltmMrPmbrDiameterSessionStatTotCreditControlRequests OBJECT-TYPE
	SYNTAX Counter64
	MAX-ACCESS read-only
	STATUS current
	DESCRIPTION
		"Displays the number of Credit Control Request messages."
	::= { ltmMrPmbrDiameterSessionStatEntry 17 }

ltmMrPmbrDiameterSessionStatTotCreditControlAnswers OBJECT-TYPE
	SYNTAX Counter64
	MAX-ACCESS read-only
	STATUS current
	DESCRIPTION
		"Displays the number of Credit Control Answers messages."
	::= { ltmMrPmbrDiameterSessionStatEntry 18 }

ltmMrPmbrDiameterSessionStatTotUserAuthorizationRequests OBJECT-TYPE
	SYNTAX Counter64
	MAX-ACCESS read-only
	STATUS current
	DESCRIPTION
		"Displays the number of User Authorization Request messages."
	::= { ltmMrPmbrDiameterSessionStatEntry 19 }

ltmMrPmbrDiameterSessionStatTotUserAuthorizationAnswers OBJECT-TYPE
	SYNTAX Counter64
	MAX-ACCESS read-only
	STATUS current
	DESCRIPTION
		"Displays the number of User Authorization Answers messages."
	::= { ltmMrPmbrDiameterSessionStatEntry 20 }

ltmMrPmbrDiameterSessionStatTotOtherRequests OBJECT-TYPE
	SYNTAX Counter64
	MAX-ACCESS read-only
	STATUS current
	DESCRIPTION
		"Displays the number of Other Request messages."
	::= { ltmMrPmbrDiameterSessionStatEntry 21 }

ltmMrPmbrDiameterSessionStatTotOtherAnswers OBJECT-TYPE
	SYNTAX Counter64
	MAX-ACCESS read-only
	STATUS current
	DESCRIPTION
		"Displays the number of Other Answers messages."
	::= { ltmMrPmbrDiameterSessionStatEntry 22 }

ltmMrPmbrDiameterSessionStatTotBadMessages OBJECT-TYPE
	SYNTAX Counter64
	MAX-ACCESS read-only
	STATUS current
	DESCRIPTION
		"Displays the number of Bad Messages."
	::= { ltmMrPmbrDiameterSessionStatEntry 23 }

ltmMrPmbrDiameterSessionStatTotRejectedUnconfiguredPeers OBJECT-TYPE
	SYNTAX Counter64
	MAX-ACCESS read-only
	STATUS current
	DESCRIPTION
		"Displays the number of Messages Rejected for Unconfigured Peers."
	::= { ltmMrPmbrDiameterSessionStatEntry 24 }

ltmMrPmbrDiameterSessionStatCurReqQueuedForRetrans OBJECT-TYPE
	SYNTAX Counter64
	MAX-ACCESS read-only
	STATUS current
	DESCRIPTION
		"Displays the number of Current Requests Queued for
	     Potential Retransmission."
	::= { ltmMrPmbrDiameterSessionStatEntry 25 }

ltmMrPmbrDiameterSessionStatTotRetransReturnedBusy OBJECT-TYPE
	SYNTAX Counter64
	MAX-ACCESS read-only
	STATUS current
	DESCRIPTION
		"Displays the number of Retransmissions Returned Busy."
	::= { ltmMrPmbrDiameterSessionStatEntry 26 }

ltmMrPmbrDiameterSessionStatTotRetransReturnedUnavail OBJECT-TYPE
	SYNTAX Counter64
	MAX-ACCESS read-only
	STATUS current
	DESCRIPTION
		"Displays the number of Retransmissions Returned Unavailable."
	::= { ltmMrPmbrDiameterSessionStatEntry 27 }

ltmMrPmbrDiameterSessionStatTotRetransReqRetransmit OBJECT-TYPE
	SYNTAX Counter64
	MAX-ACCESS read-only
	STATUS current
	DESCRIPTION
		"Displays the number of Retransmission Requests Retransmitted."
	::= { ltmMrPmbrDiameterSessionStatEntry 28 }

ltmMrPmbrDiameterSessionStatTotRetransmissionTimeout OBJECT-TYPE
	SYNTAX Counter64
	MAX-ACCESS read-only
	STATUS current
	DESCRIPTION
		"Displays the number of Retransmissions due to Timeout."
	::= { ltmMrPmbrDiameterSessionStatEntry 29 }

ltmMrPmbrDiameterSessionStatTotRetransmissionErrorCode OBJECT-TYPE
	SYNTAX Counter64
	MAX-ACCESS read-only
	STATUS current
	DESCRIPTION
		"Displays the number of Retransmissions due to Matched Error Code."
	::= { ltmMrPmbrDiameterSessionStatEntry 30 }

ltmMrPmbrDiameterSessionStatTotRetransmissionIrule OBJECT-TYPE
	SYNTAX Counter64
	MAX-ACCESS read-only
	STATUS current
	DESCRIPTION
		"Displays the number of Retransmissions due to iRule."
	::= { ltmMrPmbrDiameterSessionStatEntry 31 }

ltmMrPmbrDiameterSessionStatTotRequestReceived OBJECT-TYPE
	SYNTAX Counter64
	MAX-ACCESS read-only
	STATUS current
	DESCRIPTION
		"Displays the number of request messages received."
	::= { ltmMrPmbrDiameterSessionStatEntry 32 }

ltmMrPmbrDiameterSessionStatTotRequestSent OBJECT-TYPE
	SYNTAX Counter64
	MAX-ACCESS read-only
	STATUS current
	DESCRIPTION
		"Displays the number of request messages sent."
	::= { ltmMrPmbrDiameterSessionStatEntry 33 }

ltmMrPmbrDiameterSessionStatTotDiscardUnroutable OBJECT-TYPE
	SYNTAX Counter64
	MAX-ACCESS read-only
	STATUS current
	DESCRIPTION
		"Displays the number of unroutable request messages dropped automatically."
	::= { ltmMrPmbrDiameterSessionStatEntry 34 }

ltmMrPmbrDiameterSessionStatTotRespondUnroutable OBJECT-TYPE
	SYNTAX Counter64
	MAX-ACCESS read-only
	STATUS current
	DESCRIPTION
		"Displays the number of unroutable request messages converted to error
	     answer messages automatically."
	::= { ltmMrPmbrDiameterSessionStatEntry 35 }

ltmMrPmbrDiameterSessionStatAveRequestLatency OBJECT-TYPE
	SYNTAX Counter64
	MAX-ACCESS read-only
	STATUS current
	DESCRIPTION
		"Displays the average L7 processing latency for diameter request messages
	     over the last second (in milliseconds)."
	::= { ltmMrPmbrDiameterSessionStatEntry 36 }

ltmMrPmbrDiameterSessionStatAveAnswerLatency OBJECT-TYPE
	SYNTAX Counter64
	MAX-ACCESS read-only
	STATUS current
	DESCRIPTION
		"Displays the average L7 processing latency for diameter answer messages
	     over the last second. (in milliseconds)."
	::= { ltmMrPmbrDiameterSessionStatEntry 37 }

ltmMrPmbrDiameterSessionStatAvePeerDelay OBJECT-TYPE
	SYNTAX Counter64
	MAX-ACCESS read-only
	STATUS current
	DESCRIPTION
		"Displays the average time between forwarding a request message to a peer and
	     receiving the answer message from that peer over the last second (in milliseconds)."
	::= { ltmMrPmbrDiameterSessionStatEntry 38 }

ltmMrPmbrDiameterSessionStatAveRoundTripTime OBJECT-TYPE
	SYNTAX Counter64
	MAX-ACCESS read-only
	STATUS current
	DESCRIPTION
		"Displays the average time between receiving a request message and
	     forwarding the answer message over the last second (in milliseconds)."
	::= { ltmMrPmbrDiameterSessionStatEntry 39 }

ltmMrPmbrDiameterSessionStatCurTrafficRate OBJECT-TYPE
	SYNTAX Counter64
	MAX-ACCESS read-only
	STATUS current
	DESCRIPTION
		"Displays the number of requests and responses sent and received over the
	     last second."
	::= { ltmMrPmbrDiameterSessionStatEntry 40 }

ltmMrPmbrDiameterSessionStatCurTimeoutRatio OBJECT-TYPE
	SYNTAX Counter64
	MAX-ACCESS read-only
	STATUS current
	DESCRIPTION
		"Displays the percentage of answer messages unanswered."
	::= { ltmMrPmbrDiameterSessionStatEntry 41 }

ltmMrPmbrDiameterSessionStatCurErrorAnswerRatio OBJECT-TYPE
	SYNTAX Counter64
	MAX-ACCESS read-only
	STATUS current
	DESCRIPTION
		"Displays the percentage of answer messages received containing an
	     error result code (3000-5999)."
	::= { ltmMrPmbrDiameterSessionStatEntry 42 }

ltmMrPmbrDiameterSessionStatTotResultCodeRcvd1xxx OBJECT-TYPE
	SYNTAX Counter64
	MAX-ACCESS read-only
	STATUS current
	DESCRIPTION
		"Displays the number of answer messages received with
	     a response code between 1000-1999."
	::= { ltmMrPmbrDiameterSessionStatEntry 43 }

ltmMrPmbrDiameterSessionStatTotResultCodeRcvd2xxx OBJECT-TYPE
	SYNTAX Counter64
	MAX-ACCESS read-only
	STATUS current
	DESCRIPTION
		"Displays the number of answer messages received with
	     a response code between 2000-2999."
	::= { ltmMrPmbrDiameterSessionStatEntry 44 }

ltmMrPmbrDiameterSessionStatTotResultCodeRcvd3xxx OBJECT-TYPE
	SYNTAX Counter64
	MAX-ACCESS read-only
	STATUS current
	DESCRIPTION
		"Displays the number of answer messages received with
	     a response code between 3000-3999."
	::= { ltmMrPmbrDiameterSessionStatEntry 45 }

ltmMrPmbrDiameterSessionStatTotResultCodeRcvd4xxx OBJECT-TYPE
	SYNTAX Counter64
	MAX-ACCESS read-only
	STATUS current
	DESCRIPTION
		"Displays the number of answer messages received with
	     a response code between 4000-4999."
	::= { ltmMrPmbrDiameterSessionStatEntry 46 }

ltmMrPmbrDiameterSessionStatTotResultCodeRcvd5xxx OBJECT-TYPE
	SYNTAX Counter64
	MAX-ACCESS read-only
	STATUS current
	DESCRIPTION
		"Displays the number of answer messages received with
	     a response code between 5000-5999."
	::= { ltmMrPmbrDiameterSessionStatEntry 47 }

ltmMrPmbrDiameterSessionStatTotResultCodeSent1xxx OBJECT-TYPE
	SYNTAX Counter64
	MAX-ACCESS read-only
	STATUS current
	DESCRIPTION
		"Displays the number of answer messages sent with a response
	     code between 1000-1999."
	::= { ltmMrPmbrDiameterSessionStatEntry 48 }

ltmMrPmbrDiameterSessionStatTotResultCodeSent2xxx OBJECT-TYPE
	SYNTAX Counter64
	MAX-ACCESS read-only
	STATUS current
	DESCRIPTION
		"Displays the number of answer messages sent with a response
	     code between 2000-2999."
	::= { ltmMrPmbrDiameterSessionStatEntry 49 }

ltmMrPmbrDiameterSessionStatTotResultCodeSent3xxx OBJECT-TYPE
	SYNTAX Counter64
	MAX-ACCESS read-only
	STATUS current
	DESCRIPTION
		"Displays the number of answer messages sent with a response
	     code between 3000-3999."
	::= { ltmMrPmbrDiameterSessionStatEntry 50 }

ltmMrPmbrDiameterSessionStatTotResultCodeSent4xxx OBJECT-TYPE
	SYNTAX Counter64
	MAX-ACCESS read-only
	STATUS current
	DESCRIPTION
		"Displays the number of answer messages sent with a response
	     code between 4000-4999."
	::= { ltmMrPmbrDiameterSessionStatEntry 51 }

ltmMrPmbrDiameterSessionStatTotResultCodeSent5xxx OBJECT-TYPE
	SYNTAX Counter64
	MAX-ACCESS read-only
	STATUS current
	DESCRIPTION
		"Displays the number of answer messages sent with a response
	     code between 5000-5999."
	::= { ltmMrPmbrDiameterSessionStatEntry 52 }

--==================================================================
-- Mr_pmbr_diameter_router_stat
--==================================================================
ltmMrPmbrDiameterRouterStatResetStats OBJECT-TYPE
	SYNTAX INTEGER
	MAX-ACCESS read-write
	STATUS current
	DESCRIPTION
		"The action to reset resettable statistics data in ltmMrPmbrDiameterRouterStat.
		 Setting this value to 1 will reset statistics data.
		 Note, some statistics data may not be reset including data that are incremental counters."
	::= { ltmMrPmbrDiameterRouterStat 1 }

ltmMrPmbrDiameterRouterStatNumber OBJECT-TYPE
	SYNTAX INTEGER
	MAX-ACCESS read-only
	STATUS current
	DESCRIPTION
		"The number of ltmMrPmbrDiameterRouterStat entries in the table."
	::= { ltmMrPmbrDiameterRouterStat 2 }

ltmMrPmbrDiameterRouterStatTable OBJECT-TYPE
	SYNTAX SEQUENCE OF LtmMrPmbrDiameterRouterStatEntry
	MAX-ACCESS not-accessible
	STATUS current
	DESCRIPTION
		"A table containing statistic information for message routing diameter router profiles."
	::= { ltmMrPmbrDiameterRouterStat 3 }

ltmMrPmbrDiameterRouterStatEntry OBJECT-TYPE
	SYNTAX  LtmMrPmbrDiameterRouterStatEntry
	MAX-ACCESS not-accessible
	STATUS current
	DESCRIPTION
		"Columns in the ltmMrPmbrDiameterRouterStat Table"
	INDEX {
		ltmMrPmbrDiameterRouterStatRouterInst,
		ltmMrPmbrDiameterRouterStatMrType,
		ltmMrPmbrDiameterRouterStatTrName,
		ltmMrPmbrDiameterRouterStatPool,
		ltmMrPmbrDiameterRouterStatAddrType,
		ltmMrPmbrDiameterRouterStatAddr,
		ltmMrPmbrDiameterRouterStatPort
	}
	::= { ltmMrPmbrDiameterRouterStatTable 1 }

LtmMrPmbrDiameterRouterStatEntry ::=
	SEQUENCE {
        	ltmMrPmbrDiameterRouterStatRouterInst                     LongDisplayString,
        	ltmMrPmbrDiameterRouterStatMrType                         LongDisplayString,
        	ltmMrPmbrDiameterRouterStatTrName                         LongDisplayString,
        	ltmMrPmbrDiameterRouterStatPool                           LongDisplayString,
        	ltmMrPmbrDiameterRouterStatAddrType                       InetAddressType,
        	ltmMrPmbrDiameterRouterStatAddr                           InetAddress,
        	ltmMrPmbrDiameterRouterStatPort                           InetPortNumber,
        	ltmMrPmbrDiameterRouterStatTotMessgesIn                   Counter64,
        	ltmMrPmbrDiameterRouterStatTotMessagesInRetry             Counter64,
        	ltmMrPmbrDiameterRouterStatTotMessagesOut                 Counter64,
        	ltmMrPmbrDiameterRouterStatTotMessagesCannotReturn        Counter64,
        	ltmMrPmbrDiameterRouterStatTotMessagesRouted              Counter64,
        	ltmMrPmbrDiameterRouterStatTotMessagesUnroutable          Counter64,
        	ltmMrPmbrDiameterRouterStatTotMessagesDropped             Counter64,
        	ltmMrPmbrDiameterRouterStatTotMessagesQueueFull           Counter64,
        	ltmMrPmbrDiameterRouterStatTotMessagesNoConnection        Counter64,
        	ltmMrPmbrDiameterRouterStatTotMessagesConnectionClosed    Counter64,
        	ltmMrPmbrDiameterRouterStatTotMessagesInternalError       Counter64,
        	ltmMrPmbrDiameterRouterStatTotMessagesPersistInUse        Counter64,
        	ltmMrPmbrDiameterRouterStatTotMessagesStandbyDropped      Counter64,
        	ltmMrPmbrDiameterRouterStatTotMessagesMaxRetries          Counter64,
        	ltmMrPmbrDiameterRouterStatTotMessagesInCloned            Counter64,
        	ltmMrPmbrDiameterRouterStatTotMessagesReturned            Counter64,
        	ltmMrPmbrDiameterRouterStatTotPayloadBytesIn              Counter64,
        	ltmMrPmbrDiameterRouterStatTotPayloadBytesOut             Counter64,
        	ltmMrPmbrDiameterRouterStatCurIncomingStreams             Counter64,
        	ltmMrPmbrDiameterRouterStatCurOutgoingStreams             Counter64,
        	ltmMrPmbrDiameterRouterStatTotIncomingStreams             Counter64,
        	ltmMrPmbrDiameterRouterStatTotOutgoingStreams             Counter64,
        	ltmMrPmbrDiameterRouterStatTotFailedOutgoingStreams       Counter64,
        	ltmMrPmbrDiameterRouterStatCurIncomingConnections         Counter64,
        	ltmMrPmbrDiameterRouterStatCurOutgoingConnections         Counter64,
        	ltmMrPmbrDiameterRouterStatCurAutoInitOutgoingConns       Counter64,
        	ltmMrPmbrDiameterRouterStatTotIncomingConnections         Counter64,
        	ltmMrPmbrDiameterRouterStatTotOutgoingConnections         Counter64,
        	ltmMrPmbrDiameterRouterStatTotAutoInitOutgoingConns       Counter64,
        	ltmMrPmbrDiameterRouterStatTotFailedOutgoingConnections   Counter64,
        	ltmMrPmbrDiameterRouterStatTotFailAutoInitOutgoingConns   Counter64,
        	ltmMrPmbrDiameterRouterStatCurPassthruConnections         Counter64,
        	ltmMrPmbrDiameterRouterStatTotPassthruConnections         Counter64,
        	ltmMrPmbrDiameterRouterStatTotFailedPassthruConnections   Counter64,
        	ltmMrPmbrDiameterRouterStatTotPassthruBytes               Counter64,
        	ltmMrPmbrDiameterRouterStatCurPendingRequests             Counter64,
        	ltmMrPmbrDiameterRouterStatTotExpiredPendingRequests      Counter64,
        	ltmMrPmbrDiameterRouterStatTotDroppedUnexpectedAnswers    Counter64,
        	ltmMrPmbrDiameterRouterStatTotDroppedLateAnswers          Counter64
	}

ltmMrPmbrDiameterRouterStatRouterInst OBJECT-TYPE
	SYNTAX LongDisplayString
	MAX-ACCESS read-only
	STATUS current
	DESCRIPTION
		"The name of the router instance."
	::= { ltmMrPmbrDiameterRouterStatEntry 1 }

ltmMrPmbrDiameterRouterStatMrType OBJECT-TYPE
	SYNTAX LongDisplayString
	MAX-ACCESS read-only
	STATUS current
	DESCRIPTION
		"The type of transport - config or virtual."
	::= { ltmMrPmbrDiameterRouterStatEntry 2 }

ltmMrPmbrDiameterRouterStatTrName OBJECT-TYPE
	SYNTAX LongDisplayString
	MAX-ACCESS read-only
	STATUS current
	DESCRIPTION
		"The name of the transport config."
	::= { ltmMrPmbrDiameterRouterStatEntry 3 }

ltmMrPmbrDiameterRouterStatPool OBJECT-TYPE
	SYNTAX LongDisplayString
	MAX-ACCESS read-only
	STATUS current
	DESCRIPTION
		"The name of the pool."
	::= { ltmMrPmbrDiameterRouterStatEntry 4 }

ltmMrPmbrDiameterRouterStatAddrType OBJECT-TYPE
	SYNTAX InetAddressType
	MAX-ACCESS read-only
	STATUS current
	DESCRIPTION
		"The IP address type of the pool member address."
	::= { ltmMrPmbrDiameterRouterStatEntry 5 }

ltmMrPmbrDiameterRouterStatAddr OBJECT-TYPE
	SYNTAX InetAddress
	MAX-ACCESS read-only
	STATUS current
	DESCRIPTION
		"The IP address of the pool member"
	::= { ltmMrPmbrDiameterRouterStatEntry 6 }

ltmMrPmbrDiameterRouterStatPort OBJECT-TYPE
	SYNTAX InetPortNumber
	MAX-ACCESS read-only
	STATUS current
	DESCRIPTION
		"The port number of the specified pool member."
	::= { ltmMrPmbrDiameterRouterStatEntry 7 }

ltmMrPmbrDiameterRouterStatTotMessgesIn OBJECT-TYPE
	SYNTAX Counter64
	MAX-ACCESS read-only
	STATUS current
	DESCRIPTION
		"Displays the number of messages received for forwarding."
	::= { ltmMrPmbrDiameterRouterStatEntry 8 }

ltmMrPmbrDiameterRouterStatTotMessagesInRetry OBJECT-TYPE
	SYNTAX Counter64
	MAX-ACCESS read-only
	STATUS current
	DESCRIPTION
		"Displays the number of retry messages received for forwarding."
	::= { ltmMrPmbrDiameterRouterStatEntry 9 }

ltmMrPmbrDiameterRouterStatTotMessagesOut OBJECT-TYPE
	SYNTAX Counter64
	MAX-ACCESS read-only
	STATUS current
	DESCRIPTION
		"Displays the number of messages forwarded or returned to the originator."
	::= { ltmMrPmbrDiameterRouterStatEntry 10 }

ltmMrPmbrDiameterRouterStatTotMessagesCannotReturn OBJECT-TYPE
	SYNTAX Counter64
	MAX-ACCESS read-only
	STATUS current
	DESCRIPTION
		"Displays the number of messages which routing failed and could not be returned to the originator."
	::= { ltmMrPmbrDiameterRouterStatEntry 11 }

ltmMrPmbrDiameterRouterStatTotMessagesRouted OBJECT-TYPE
	SYNTAX Counter64
	MAX-ACCESS read-only
	STATUS current
	DESCRIPTION
		"Displays the number of messages where a route was successfully found."
	::= { ltmMrPmbrDiameterRouterStatEntry 12 }

ltmMrPmbrDiameterRouterStatTotMessagesUnroutable OBJECT-TYPE
	SYNTAX Counter64
	MAX-ACCESS read-only
	STATUS current
	DESCRIPTION
		"Displays the number of messages where no route was found."
	::= { ltmMrPmbrDiameterRouterStatEntry 13 }

ltmMrPmbrDiameterRouterStatTotMessagesDropped OBJECT-TYPE
	SYNTAX Counter64
	MAX-ACCESS read-only
	STATUS current
	DESCRIPTION
		"Displays the number of messages dropped via an iRule."
	::= { ltmMrPmbrDiameterRouterStatEntry 14 }

ltmMrPmbrDiameterRouterStatTotMessagesQueueFull OBJECT-TYPE
	SYNTAX Counter64
	MAX-ACCESS read-only
	STATUS current
	DESCRIPTION
		"Displays the number of messages which were routed but the outgoing
	     queue for the destination was full."
	::= { ltmMrPmbrDiameterRouterStatEntry 15 }

ltmMrPmbrDiameterRouterStatTotMessagesNoConnection OBJECT-TYPE
	SYNTAX Counter64
	MAX-ACCESS read-only
	STATUS current
	DESCRIPTION
		"Displays the number of messages which were routed to a connection which was closed before the
	      message could be delivered."
	::= { ltmMrPmbrDiameterRouterStatEntry 16 }

ltmMrPmbrDiameterRouterStatTotMessagesConnectionClosed OBJECT-TYPE
	SYNTAX Counter64
	MAX-ACCESS read-only
	STATUS current
	DESCRIPTION
		"Displays the number of messages which were pending delivery when the connection closed."
	::= { ltmMrPmbrDiameterRouterStatEntry 17 }

ltmMrPmbrDiameterRouterStatTotMessagesInternalError OBJECT-TYPE
	SYNTAX Counter64
	MAX-ACCESS read-only
	STATUS current
	DESCRIPTION
		"Displays the number of messages which were not routed due to an internal error ."
	::= { ltmMrPmbrDiameterRouterStatEntry 18 }

ltmMrPmbrDiameterRouterStatTotMessagesPersistInUse OBJECT-TYPE
	SYNTAX Counter64
	MAX-ACCESS read-only
	STATUS current
	DESCRIPTION
		"Displays the number of messages which after routing failed to add a persistence entry because it
	     was already in use."
	::= { ltmMrPmbrDiameterRouterStatEntry 19 }

ltmMrPmbrDiameterRouterStatTotMessagesStandbyDropped OBJECT-TYPE
	SYNTAX Counter64
	MAX-ACCESS read-only
	STATUS current
	DESCRIPTION
		"Displays the number of messages which were dropped on the
	     standby device."
	::= { ltmMrPmbrDiameterRouterStatEntry 20 }

ltmMrPmbrDiameterRouterStatTotMessagesMaxRetries OBJECT-TYPE
	SYNTAX Counter64
	MAX-ACCESS read-only
	STATUS current
	DESCRIPTION
		"Displays the number of messages returned to the originator because the latest attempt to retry
	     routing exceeded the configured max retry count."
	::= { ltmMrPmbrDiameterRouterStatEntry 21 }

ltmMrPmbrDiameterRouterStatTotMessagesInCloned OBJECT-TYPE
	SYNTAX Counter64
	MAX-ACCESS read-only
	STATUS current
	DESCRIPTION
		"Displays the total number of messages cloned per route."
	::= { ltmMrPmbrDiameterRouterStatEntry 22 }

ltmMrPmbrDiameterRouterStatTotMessagesReturned OBJECT-TYPE
	SYNTAX Counter64
	MAX-ACCESS read-only
	STATUS current
	DESCRIPTION
		"Displays the number of messages returned."
	::= { ltmMrPmbrDiameterRouterStatEntry 23 }

ltmMrPmbrDiameterRouterStatTotPayloadBytesIn OBJECT-TYPE
	SYNTAX Counter64
	MAX-ACCESS read-only
	STATUS current
	DESCRIPTION
		"Displays the number of bytes of payload received."
	::= { ltmMrPmbrDiameterRouterStatEntry 24 }

ltmMrPmbrDiameterRouterStatTotPayloadBytesOut OBJECT-TYPE
	SYNTAX Counter64
	MAX-ACCESS read-only
	STATUS current
	DESCRIPTION
		"Displays the number of bytes of payload sent."
	::= { ltmMrPmbrDiameterRouterStatEntry 25 }

ltmMrPmbrDiameterRouterStatCurIncomingStreams OBJECT-TYPE
	SYNTAX Counter64
	MAX-ACCESS read-only
	STATUS current
	DESCRIPTION
		"Displays the number of active incoming streams."
	::= { ltmMrPmbrDiameterRouterStatEntry 26 }

ltmMrPmbrDiameterRouterStatCurOutgoingStreams OBJECT-TYPE
	SYNTAX Counter64
	MAX-ACCESS read-only
	STATUS current
	DESCRIPTION
		"Displays the number of active outgoing streams."
	::= { ltmMrPmbrDiameterRouterStatEntry 27 }

ltmMrPmbrDiameterRouterStatTotIncomingStreams OBJECT-TYPE
	SYNTAX Counter64
	MAX-ACCESS read-only
	STATUS current
	DESCRIPTION
		"Displays the total number of incoming streams since TMM restart or stats reset."
	::= { ltmMrPmbrDiameterRouterStatEntry 28 }

ltmMrPmbrDiameterRouterStatTotOutgoingStreams OBJECT-TYPE
	SYNTAX Counter64
	MAX-ACCESS read-only
	STATUS current
	DESCRIPTION
		"Displays the total number of outgoing streams since TMM restart or stats reset."
	::= { ltmMrPmbrDiameterRouterStatEntry 29 }

ltmMrPmbrDiameterRouterStatTotFailedOutgoingStreams OBJECT-TYPE
	SYNTAX Counter64
	MAX-ACCESS read-only
	STATUS current
	DESCRIPTION
		"Displays the total number of failed outgoing streams since TMM restart or stats reset."
	::= { ltmMrPmbrDiameterRouterStatEntry 30 }

ltmMrPmbrDiameterRouterStatCurIncomingConnections OBJECT-TYPE
	SYNTAX Counter64
	MAX-ACCESS read-only
	STATUS current
	DESCRIPTION
		"Displays the number of active incoming connections."
	::= { ltmMrPmbrDiameterRouterStatEntry 31 }

ltmMrPmbrDiameterRouterStatCurOutgoingConnections OBJECT-TYPE
	SYNTAX Counter64
	MAX-ACCESS read-only
	STATUS current
	DESCRIPTION
		"Displays the number of active outgoing connections (including outgoing connections created by
	     auto-initialization)."
	::= { ltmMrPmbrDiameterRouterStatEntry 32 }

ltmMrPmbrDiameterRouterStatCurAutoInitOutgoingConns OBJECT-TYPE
	SYNTAX Counter64
	MAX-ACCESS read-only
	STATUS current
	DESCRIPTION
		"Displays the number of active outgoing connections created by auto-initialization."
	::= { ltmMrPmbrDiameterRouterStatEntry 33 }

ltmMrPmbrDiameterRouterStatTotIncomingConnections OBJECT-TYPE
	SYNTAX Counter64
	MAX-ACCESS read-only
	STATUS current
	DESCRIPTION
		"Displays the total number of incoming connections created since TMM restart or stats reset."
	::= { ltmMrPmbrDiameterRouterStatEntry 34 }

ltmMrPmbrDiameterRouterStatTotOutgoingConnections OBJECT-TYPE
	SYNTAX Counter64
	MAX-ACCESS read-only
	STATUS current
	DESCRIPTION
		"Displays the total number of outgoing connections created since TMM restart or stats reset
	     (including outgoing connections created by auto-initialization)."
	::= { ltmMrPmbrDiameterRouterStatEntry 35 }

ltmMrPmbrDiameterRouterStatTotAutoInitOutgoingConns OBJECT-TYPE
	SYNTAX Counter64
	MAX-ACCESS read-only
	STATUS current
	DESCRIPTION
		"Displays the total number of outgoing connections created by auto-initialization since
	      TMM restart or stats reset."
	::= { ltmMrPmbrDiameterRouterStatEntry 36 }

ltmMrPmbrDiameterRouterStatTotFailedOutgoingConnections OBJECT-TYPE
	SYNTAX Counter64
	MAX-ACCESS read-only
	STATUS current
	DESCRIPTION
		"Displays the total number of outgoing connections that failed to be established."
	::= { ltmMrPmbrDiameterRouterStatEntry 37 }

ltmMrPmbrDiameterRouterStatTotFailAutoInitOutgoingConns OBJECT-TYPE
	SYNTAX Counter64
	MAX-ACCESS read-only
	STATUS current
	DESCRIPTION
		"Displays the total number of outgoing connections that failed to be established by
	     auto-initalization."
	::= { ltmMrPmbrDiameterRouterStatEntry 38 }

ltmMrPmbrDiameterRouterStatCurPassthruConnections OBJECT-TYPE
	SYNTAX Counter64
	MAX-ACCESS read-only
	STATUS current
	DESCRIPTION
		"Displays the number of active pass through connections."
	::= { ltmMrPmbrDiameterRouterStatEntry 39 }

ltmMrPmbrDiameterRouterStatTotPassthruConnections OBJECT-TYPE
	SYNTAX Counter64
	MAX-ACCESS read-only
	STATUS current
	DESCRIPTION
		"Displays the total number of pass through connections since TMM restart or stats reset."
	::= { ltmMrPmbrDiameterRouterStatEntry 40 }

ltmMrPmbrDiameterRouterStatTotFailedPassthruConnections OBJECT-TYPE
	SYNTAX Counter64
	MAX-ACCESS read-only
	STATUS current
	DESCRIPTION
		"Displays the total number of failed pass through connections since TMM restart or stats reset."
	::= { ltmMrPmbrDiameterRouterStatEntry 41 }

ltmMrPmbrDiameterRouterStatTotPassthruBytes OBJECT-TYPE
	SYNTAX Counter64
	MAX-ACCESS read-only
	STATUS current
	DESCRIPTION
		"Displays the number of pass through bytes."
	::= { ltmMrPmbrDiameterRouterStatEntry 42 }

ltmMrPmbrDiameterRouterStatCurPendingRequests OBJECT-TYPE
	SYNTAX Counter64
	MAX-ACCESS read-only
	STATUS current
	DESCRIPTION
		"Displays the current number of pending request messages awaiting answer
	     responses."
	::= { ltmMrPmbrDiameterRouterStatEntry 43 }

ltmMrPmbrDiameterRouterStatTotExpiredPendingRequests OBJECT-TYPE
	SYNTAX Counter64
	MAX-ACCESS read-only
	STATUS current
	DESCRIPTION
		"Displays the total number of expired pending requests. An expired
	     pending request is a request that did not receive an answer within twice the transaction timeout as
	      detected by the pending request sweeper."
	::= { ltmMrPmbrDiameterRouterStatEntry 44 }

ltmMrPmbrDiameterRouterStatTotDroppedUnexpectedAnswers OBJECT-TYPE
	SYNTAX Counter64
	MAX-ACCESS read-only
	STATUS current
	DESCRIPTION
		"Displays the number of unexpected answer messages. An unexpected
	     answer message is an answer that did have a corresponding pending request message."
	::= { ltmMrPmbrDiameterRouterStatEntry 45 }

ltmMrPmbrDiameterRouterStatTotDroppedLateAnswers OBJECT-TYPE
	SYNTAX Counter64
	MAX-ACCESS read-only
	STATUS current
	DESCRIPTION
		"Displays the number of answers dropped because the corresponding
	     request has been retransmitted."
	::= { ltmMrPmbrDiameterRouterStatEntry 46 }

--==================================================================
-- Profile_sipsession_stat
--==================================================================
ltmSipsessionProfileStatResetStats OBJECT-TYPE
	SYNTAX INTEGER
	MAX-ACCESS read-write
	STATUS current
	DESCRIPTION
		"The action to reset resettable statistics data in ltmSipsessionProfileStat.
		 Setting this value to 1 will reset statistics data.
		 Note, some statistics data may not be reset including data that are incremental counters."
	::= { ltmSipsessionProfileStat 1 }

ltmSipsessionProfileStatNumber OBJECT-TYPE
	SYNTAX INTEGER
	MAX-ACCESS read-only
	STATUS current
	DESCRIPTION
		"The number of ltmSipsessionProfileStat entries in the table."
	::= { ltmSipsessionProfileStat 2 }

ltmSipsessionProfileStatTable OBJECT-TYPE
	SYNTAX SEQUENCE OF LtmSipsessionProfileStatEntry
	MAX-ACCESS not-accessible
	STATUS current
	DESCRIPTION
		"A table containing statistic information for SIP session profiles."
	::= { ltmSipsessionProfileStat 3 }

ltmSipsessionProfileStatEntry OBJECT-TYPE
	SYNTAX  LtmSipsessionProfileStatEntry
	MAX-ACCESS not-accessible
	STATUS current
	DESCRIPTION
		"Columns in the ltmSipsessionProfileStat Table"
	INDEX {
		ltmSipsessionProfileStatName,
		ltmSipsessionProfileStatVsName
	}
	::= { ltmSipsessionProfileStatTable 1 }

LtmSipsessionProfileStatEntry ::=
	SEQUENCE {
        	ltmSipsessionProfileStatName                              LongDisplayString,
        	ltmSipsessionProfileStatVsName                            LongDisplayString,
        	ltmSipsessionProfileStatRequests                          Counter64,
        	ltmSipsessionProfileStatResponses                         Counter64,
        	ltmSipsessionProfileStatBadmsgs                           Counter64,
        	ltmSipsessionProfileStatBadmsgsReq                        Counter64,
        	ltmSipsessionProfileStatDrops                             Counter64,
        	ltmSipsessionProfileStatDropsReq                          Counter64,
        	ltmSipsessionProfileStatInvite                            Counter64,
        	ltmSipsessionProfileStatAck                               Counter64,
        	ltmSipsessionProfileStatBye                               Counter64,
        	ltmSipsessionProfileStatCancel                            Counter64,
        	ltmSipsessionProfileStatOptions                           Counter64,
        	ltmSipsessionProfileStatRegisterReq                       Counter64,
        	ltmSipsessionProfileStatPrack                             Counter64,
        	ltmSipsessionProfileStatSubscribe                         Counter64,
        	ltmSipsessionProfileStatNotify                            Counter64,
        	ltmSipsessionProfileStatPublish                           Counter64,
        	ltmSipsessionProfileStatInfo                              Counter64,
        	ltmSipsessionProfileStatRefer                             Counter64,
        	ltmSipsessionProfileStatMessage                           Counter64,
        	ltmSipsessionProfileStatUpdateReq                         Counter64,
        	ltmSipsessionProfileStatService                           Counter64,
        	ltmSipsessionProfileStatBenotify                          Counter64,
        	ltmSipsessionProfileStatNegotiate                         Counter64,
        	ltmSipsessionProfileStatOther                             Counter64,
        	ltmSipsessionProfileStatProvisional                       Counter64,
        	ltmSipsessionProfileStatSuccessful                        Counter64,
        	ltmSipsessionProfileStatRedirection                       Counter64,
        	ltmSipsessionProfileStatClientFailures                    Counter64,
        	ltmSipsessionProfileStatServerFailures                    Counter64,
        	ltmSipsessionProfileStatGlobalFailures                    Counter64,
        	ltmSipsessionProfileStatBadRequest                        Counter64,
        	ltmSipsessionProfileStatBadRequest400Sent                 Counter64,
        	ltmSipsessionProfileStatNotFound                          Counter64,
        	ltmSipsessionProfileStatNotFound404Sent                   Counter64,
        	ltmSipsessionProfileStatRequestEntityTooLarge             Counter64,
        	ltmSipsessionProfileStatRequestEntityTooLarge413Sent      Counter64,
        	ltmSipsessionProfileStatUnsupportedUriScheme              Counter64,
        	ltmSipsessionProfileStatUnsupportedUriScheme416Sent       Counter64,
        	ltmSipsessionProfileStatTemporarilyUnavailable            Counter64,
        	ltmSipsessionProfileStatTemporarilyUnavailable480Sent     Counter64,
        	ltmSipsessionProfileStatTransactionDoesNotExist           Counter64,
        	ltmSipsessionProfileStatTransactionDoesNotExist481Sent    Counter64,
        	ltmSipsessionProfileStatLoopDetected                      Counter64,
        	ltmSipsessionProfileStatLoopDetected482Sent               Counter64,
        	ltmSipsessionProfileStatTooManyHops                       Counter64,
        	ltmSipsessionProfileStatTooManyHops483Sent                Counter64,
        	ltmSipsessionProfileStatAddressIncomplete                 Counter64,
        	ltmSipsessionProfileStatAddressIncomplete484Sent          Counter64,
        	ltmSipsessionProfileStatNotAcceptableHere                 Counter64,
        	ltmSipsessionProfileStatNotAcceptableHere488Sent          Counter64,
        	ltmSipsessionProfileStatServerInternalError               Counter64,
        	ltmSipsessionProfileStatServerInternalError500Sent        Counter64,
        	ltmSipsessionProfileStatNotImplemented                    Counter64,
        	ltmSipsessionProfileStatNotImplemented501Sent             Counter64,
        	ltmSipsessionProfileStatServiceUnavailable                Counter64,
        	ltmSipsessionProfileStatServiceUnavailable503Sent         Counter64,
        	ltmSipsessionProfileStatVersionNotSupported               Counter64,
        	ltmSipsessionProfileStatVersionNotSupported505Sent        Counter64
	}

ltmSipsessionProfileStatName OBJECT-TYPE
	SYNTAX LongDisplayString
	MAX-ACCESS read-only
	STATUS current
	DESCRIPTION
		"The Name of the SIP session profile."
	::= { ltmSipsessionProfileStatEntry 1 }

ltmSipsessionProfileStatVsName OBJECT-TYPE
	SYNTAX LongDisplayString
	MAX-ACCESS read-only
	STATUS current
	DESCRIPTION
		"The Name of the virtual server."
	::= { ltmSipsessionProfileStatEntry 2 }

ltmSipsessionProfileStatRequests OBJECT-TYPE
	SYNTAX Counter64
	MAX-ACCESS read-only
	STATUS current
	DESCRIPTION
		"Displays the number of SIP request messages the system handled."
	::= { ltmSipsessionProfileStatEntry 3 }

ltmSipsessionProfileStatResponses OBJECT-TYPE
	SYNTAX Counter64
	MAX-ACCESS read-only
	STATUS current
	DESCRIPTION
		"Displays the number of SIP response messages the system handled."
	::= { ltmSipsessionProfileStatEntry 4 }

ltmSipsessionProfileStatBadmsgs OBJECT-TYPE
	SYNTAX Counter64
	MAX-ACCESS read-only
	STATUS current
	DESCRIPTION
		"Displays the number of bad SIP messages the system handled."
	::= { ltmSipsessionProfileStatEntry 5 }

ltmSipsessionProfileStatBadmsgsReq OBJECT-TYPE
	SYNTAX Counter64
	MAX-ACCESS read-only
	STATUS current
	DESCRIPTION
		"Displays the number of bad SIP request messages the system handled."
	::= { ltmSipsessionProfileStatEntry 6 }

ltmSipsessionProfileStatDrops OBJECT-TYPE
	SYNTAX Counter64
	MAX-ACCESS read-only
	STATUS current
	DESCRIPTION
		"Displays the total number of SIP messages the system dropped."
	::= { ltmSipsessionProfileStatEntry 7 }

ltmSipsessionProfileStatDropsReq OBJECT-TYPE
	SYNTAX Counter64
	MAX-ACCESS read-only
	STATUS current
	DESCRIPTION
		"Displays the number of SIP request messages the system dropped."
	::= { ltmSipsessionProfileStatEntry 8 }

ltmSipsessionProfileStatInvite OBJECT-TYPE
	SYNTAX Counter64
	MAX-ACCESS read-only
	STATUS current
	DESCRIPTION
		"Displays the number of INVITE SIP request messages the system handled."
	::= { ltmSipsessionProfileStatEntry 9 }

ltmSipsessionProfileStatAck OBJECT-TYPE
	SYNTAX Counter64
	MAX-ACCESS read-only
	STATUS current
	DESCRIPTION
		"Displays the number of ACK SIP request messages the system handled."
	::= { ltmSipsessionProfileStatEntry 10 }

ltmSipsessionProfileStatBye OBJECT-TYPE
	SYNTAX Counter64
	MAX-ACCESS read-only
	STATUS current
	DESCRIPTION
		"Displays the number of BYE SIP request messages the system handled."
	::= { ltmSipsessionProfileStatEntry 11 }

ltmSipsessionProfileStatCancel OBJECT-TYPE
	SYNTAX Counter64
	MAX-ACCESS read-only
	STATUS current
	DESCRIPTION
		"Displays the number of CANCEL SIP request messages the system handled."
	::= { ltmSipsessionProfileStatEntry 12 }

ltmSipsessionProfileStatOptions OBJECT-TYPE
	SYNTAX Counter64
	MAX-ACCESS read-only
	STATUS current
	DESCRIPTION
		"Displays the number of OPTIONS SIP request messages the system handled."
	::= { ltmSipsessionProfileStatEntry 13 }

ltmSipsessionProfileStatRegisterReq OBJECT-TYPE
	SYNTAX Counter64
	MAX-ACCESS read-only
	STATUS current
	DESCRIPTION
		"Displays the number of REGISTER SIP request messages the system handled."
	::= { ltmSipsessionProfileStatEntry 14 }

ltmSipsessionProfileStatPrack OBJECT-TYPE
	SYNTAX Counter64
	MAX-ACCESS read-only
	STATUS current
	DESCRIPTION
		"Displays the number of PRACK SIP request messages the system handled."
	::= { ltmSipsessionProfileStatEntry 15 }

ltmSipsessionProfileStatSubscribe OBJECT-TYPE
	SYNTAX Counter64
	MAX-ACCESS read-only
	STATUS current
	DESCRIPTION
		"Displays the number of SUBSCRIBE SIP request messages the system handled."
	::= { ltmSipsessionProfileStatEntry 16 }

ltmSipsessionProfileStatNotify OBJECT-TYPE
	SYNTAX Counter64
	MAX-ACCESS read-only
	STATUS current
	DESCRIPTION
		"Displays the number of NOTIFY SIP request messages the system handled."
	::= { ltmSipsessionProfileStatEntry 17 }

ltmSipsessionProfileStatPublish OBJECT-TYPE
	SYNTAX Counter64
	MAX-ACCESS read-only
	STATUS current
	DESCRIPTION
		"Displays the number of PUBLISH SIP request messages the system handled."
	::= { ltmSipsessionProfileStatEntry 18 }

ltmSipsessionProfileStatInfo OBJECT-TYPE
	SYNTAX Counter64
	MAX-ACCESS read-only
	STATUS current
	DESCRIPTION
		"Displays the number of INFO SIP request messages the system handled."
	::= { ltmSipsessionProfileStatEntry 19 }

ltmSipsessionProfileStatRefer OBJECT-TYPE
	SYNTAX Counter64
	MAX-ACCESS read-only
	STATUS current
	DESCRIPTION
		"Displays the number of REFER SIP request messages the system handled."
	::= { ltmSipsessionProfileStatEntry 20 }

ltmSipsessionProfileStatMessage OBJECT-TYPE
	SYNTAX Counter64
	MAX-ACCESS read-only
	STATUS current
	DESCRIPTION
		"Displays the number of MESSAGE SIP request messages the system handled."
	::= { ltmSipsessionProfileStatEntry 21 }

ltmSipsessionProfileStatUpdateReq OBJECT-TYPE
	SYNTAX Counter64
	MAX-ACCESS read-only
	STATUS current
	DESCRIPTION
		"Displays the number of UPDATE SIP request messages the system handled."
	::= { ltmSipsessionProfileStatEntry 22 }

ltmSipsessionProfileStatService OBJECT-TYPE
	SYNTAX Counter64
	MAX-ACCESS read-only
	STATUS current
	DESCRIPTION
		"Displays the number of SERVICE SIP request messages the system handled."
	::= { ltmSipsessionProfileStatEntry 23 }

ltmSipsessionProfileStatBenotify OBJECT-TYPE
	SYNTAX Counter64
	MAX-ACCESS read-only
	STATUS current
	DESCRIPTION
		"Displays the number of BENOTIFY SIP request messages the system handled."
	::= { ltmSipsessionProfileStatEntry 24 }

ltmSipsessionProfileStatNegotiate OBJECT-TYPE
	SYNTAX Counter64
	MAX-ACCESS read-only
	STATUS current
	DESCRIPTION
		"Displays the number of NEGOTIATE SIP request messages the system handled."
	::= { ltmSipsessionProfileStatEntry 25 }

ltmSipsessionProfileStatOther OBJECT-TYPE
	SYNTAX Counter64
	MAX-ACCESS read-only
	STATUS current
	DESCRIPTION
		"Displays the number of OTHER SIP request messages the system handled."
	::= { ltmSipsessionProfileStatEntry 26 }

ltmSipsessionProfileStatProvisional OBJECT-TYPE
	SYNTAX Counter64
	MAX-ACCESS read-only
	STATUS current
	DESCRIPTION
		"Displays the number of Provisional SIP response messages the system handled."
	::= { ltmSipsessionProfileStatEntry 27 }

ltmSipsessionProfileStatSuccessful OBJECT-TYPE
	SYNTAX Counter64
	MAX-ACCESS read-only
	STATUS current
	DESCRIPTION
		"Displays the number of Successful SIP response messages the system handled."
	::= { ltmSipsessionProfileStatEntry 28 }

ltmSipsessionProfileStatRedirection OBJECT-TYPE
	SYNTAX Counter64
	MAX-ACCESS read-only
	STATUS current
	DESCRIPTION
		"Displays the number of Redirection SIP response messages the system handled."
	::= { ltmSipsessionProfileStatEntry 29 }

ltmSipsessionProfileStatClientFailures OBJECT-TYPE
	SYNTAX Counter64
	MAX-ACCESS read-only
	STATUS current
	DESCRIPTION
		"Displays the number of Client Failure SIP response messages the system handled."
	::= { ltmSipsessionProfileStatEntry 30 }

ltmSipsessionProfileStatServerFailures OBJECT-TYPE
	SYNTAX Counter64
	MAX-ACCESS read-only
	STATUS current
	DESCRIPTION
		"Displays the number of Server Failure SIP response messages the system handled."
	::= { ltmSipsessionProfileStatEntry 31 }

ltmSipsessionProfileStatGlobalFailures OBJECT-TYPE
	SYNTAX Counter64
	MAX-ACCESS read-only
	STATUS current
	DESCRIPTION
		"Displays the number of Global Failure SIP response messages the system handled."
	::= { ltmSipsessionProfileStatEntry 32 }

ltmSipsessionProfileStatBadRequest OBJECT-TYPE
	SYNTAX Counter64
	MAX-ACCESS read-only
	STATUS current
	DESCRIPTION
		"Displays the number of Bad-Request failure response messages generated when
	      rejecting a SIP message due to a malformed syntax."
	::= { ltmSipsessionProfileStatEntry 33 }

ltmSipsessionProfileStatBadRequest400Sent OBJECT-TYPE
	SYNTAX Counter64
	MAX-ACCESS read-only
	STATUS current
	DESCRIPTION
		"Displays the number of Bad-Request failure response messages sent when
	      rejecting a SIP message due to a malformed syntax."
	::= { ltmSipsessionProfileStatEntry 34 }

ltmSipsessionProfileStatNotFound OBJECT-TYPE
	SYNTAX Counter64
	MAX-ACCESS read-only
	STATUS current
	DESCRIPTION
		"Displays the number of Bad-Request failure response messages generated when rejecting
	      a SIP message when there is no matching user registration entry."
	::= { ltmSipsessionProfileStatEntry 35 }

ltmSipsessionProfileStatNotFound404Sent OBJECT-TYPE
	SYNTAX Counter64
	MAX-ACCESS read-only
	STATUS current
	DESCRIPTION
		"Displays the number of Bad-Request failure response messages sent when
	      rejecting a SIP message when there is no matching user registration entry."
	::= { ltmSipsessionProfileStatEntry 36 }

ltmSipsessionProfileStatRequestEntityTooLarge OBJECT-TYPE
	SYNTAX Counter64
	MAX-ACCESS read-only
	STATUS current
	DESCRIPTION
		"Displays the number of Request-Entity-Too-Large response
	      messages generated when rejecting a SIP message due to some aspect of the message exceeding a
	      configured size limit."
	::= { ltmSipsessionProfileStatEntry 37 }

ltmSipsessionProfileStatRequestEntityTooLarge413Sent OBJECT-TYPE
	SYNTAX Counter64
	MAX-ACCESS read-only
	STATUS current
	DESCRIPTION
		"Displays the number of Request-Entity-Too-Large response
	      messages sent when rejecting a SIP message due to some aspect of the message exceeding a
	      configured size limit."
	::= { ltmSipsessionProfileStatEntry 38 }

ltmSipsessionProfileStatUnsupportedUriScheme OBJECT-TYPE
	SYNTAX Counter64
	MAX-ACCESS read-only
	STATUS current
	DESCRIPTION
		"Displays the number of Unsupported-URI-Scheme responses messages
	      generated when rejecting a SIP message due to malformed URI."
	::= { ltmSipsessionProfileStatEntry 39 }

ltmSipsessionProfileStatUnsupportedUriScheme416Sent OBJECT-TYPE
	SYNTAX Counter64
	MAX-ACCESS read-only
	STATUS current
	DESCRIPTION
		"Displays the number of Unsupported-URI-Scheme responses
	      messages sent when rejecting a SIP message due to malformed URI."
	::= { ltmSipsessionProfileStatEntry 40 }

ltmSipsessionProfileStatTemporarilyUnavailable OBJECT-TYPE
	SYNTAX Counter64
	MAX-ACCESS read-only
	STATUS current
	DESCRIPTION
		"Displays the number of Temporary Unavailable failure response
	      messages generated when rejecting a call when the user is not available at this time."
	::= { ltmSipsessionProfileStatEntry 41 }

ltmSipsessionProfileStatTemporarilyUnavailable480Sent OBJECT-TYPE
	SYNTAX Counter64
	MAX-ACCESS read-only
	STATUS current
	DESCRIPTION
		"Displays the number of Temporary Unavailable failure
	      response messages sent when rejecting a call when the user is not available at this time."
	::= { ltmSipsessionProfileStatEntry 42 }

ltmSipsessionProfileStatTransactionDoesNotExist OBJECT-TYPE
	SYNTAX Counter64
	MAX-ACCESS read-only
	STATUS current
	DESCRIPTION
		"Displays the number of transaction does not exist response
	      message generated when response or request message is not able to be matched to a SIP transaction."
	::= { ltmSipsessionProfileStatEntry 43 }

ltmSipsessionProfileStatTransactionDoesNotExist481Sent OBJECT-TYPE
	SYNTAX Counter64
	MAX-ACCESS read-only
	STATUS current
	DESCRIPTION
		"Displays the number of transaction does not exist response
	      message sent when response or request message is not able to be matched to a SIP transaction."
	::= { ltmSipsessionProfileStatEntry 44 }

ltmSipsessionProfileStatLoopDetected OBJECT-TYPE
	SYNTAX Counter64
	MAX-ACCESS read-only
	STATUS current
	DESCRIPTION
		"Displays the number of Loop-Detected failure response messages generated
	      when rejecting a SIP message due to loop detection."
	::= { ltmSipsessionProfileStatEntry 45 }

ltmSipsessionProfileStatLoopDetected482Sent OBJECT-TYPE
	SYNTAX Counter64
	MAX-ACCESS read-only
	STATUS current
	DESCRIPTION
		"Displays the number of Loop-Detected failure response messages sent
	      when rejecting a SIP message due to loop detection."
	::= { ltmSipsessionProfileStatEntry 46 }

ltmSipsessionProfileStatTooManyHops OBJECT-TYPE
	SYNTAX Counter64
	MAX-ACCESS read-only
	STATUS current
	DESCRIPTION
		"Displays the number of Too-Many-Hops failure response messages generated
	      when rejecting a SIP message as Max-Forwards header has reached value '0'."
	::= { ltmSipsessionProfileStatEntry 47 }

ltmSipsessionProfileStatTooManyHops483Sent OBJECT-TYPE
	SYNTAX Counter64
	MAX-ACCESS read-only
	STATUS current
	DESCRIPTION
		"Displays the number of Too-Many-Hops failure response messages sent
	      when rejecting a SIP message as Max-Forwards header has reached value '0'."
	::= { ltmSipsessionProfileStatEntry 48 }

ltmSipsessionProfileStatAddressIncomplete OBJECT-TYPE
	SYNTAX Counter64
	MAX-ACCESS read-only
	STATUS current
	DESCRIPTION
		"Displays the number of Address-Incomplete failure response
	      messages generated when rejecting a SIP message due to malformed or incomplete request URI."
	::= { ltmSipsessionProfileStatEntry 49 }

ltmSipsessionProfileStatAddressIncomplete484Sent OBJECT-TYPE
	SYNTAX Counter64
	MAX-ACCESS read-only
	STATUS current
	DESCRIPTION
		"Displays the number of Address-Incomplete failure
	      response messages sent when rejecting a SIP message due to malformed or incomplete request URI."
	::= { ltmSipsessionProfileStatEntry 50 }

ltmSipsessionProfileStatNotAcceptableHere OBJECT-TYPE
	SYNTAX Counter64
	MAX-ACCESS read-only
	STATUS current
	DESCRIPTION
		"Displays the number of Not-Acceptable failure response
	      messages generated when rejecting a SIP message containing too many SDP media requests."
	::= { ltmSipsessionProfileStatEntry 51 }

ltmSipsessionProfileStatNotAcceptableHere488Sent OBJECT-TYPE
	SYNTAX Counter64
	MAX-ACCESS read-only
	STATUS current
	DESCRIPTION
		"Displays the number of Not-Acceptable failure response
	      messages sent when rejecting a SIP message containing too many SDP media requests."
	::= { ltmSipsessionProfileStatEntry 52 }

ltmSipsessionProfileStatServerInternalError OBJECT-TYPE
	SYNTAX Counter64
	MAX-ACCESS read-only
	STATUS current
	DESCRIPTION
		"Displays the number of Server-Internal-Error failure response
	      messages generated when rejecting a SIP message due to some unexpected condition and cannot
	      fulfill the request."
	::= { ltmSipsessionProfileStatEntry 53 }

ltmSipsessionProfileStatServerInternalError500Sent OBJECT-TYPE
	SYNTAX Counter64
	MAX-ACCESS read-only
	STATUS current
	DESCRIPTION
		"Displays the number of Server-Internal-Error failure response
	      messages sent when rejecting a SIP message due to some unexpected condition and cannot
	      fulfill the request."
	::= { ltmSipsessionProfileStatEntry 54 }

ltmSipsessionProfileStatNotImplemented OBJECT-TYPE
	SYNTAX Counter64
	MAX-ACCESS read-only
	STATUS current
	DESCRIPTION
		"Displays the number of Not-Implemented failure response messages generated
	      when rejecting a SIP message due to an invalid/unimplemented request method."
	::= { ltmSipsessionProfileStatEntry 55 }

ltmSipsessionProfileStatNotImplemented501Sent OBJECT-TYPE
	SYNTAX Counter64
	MAX-ACCESS read-only
	STATUS current
	DESCRIPTION
		"Displays the number of Not-Implemented failure response messages
	      sent when rejecting a SIP message due to an invalid/unimplemented request method."
	::= { ltmSipsessionProfileStatEntry 56 }

ltmSipsessionProfileStatServiceUnavailable OBJECT-TYPE
	SYNTAX Counter64
	MAX-ACCESS read-only
	STATUS current
	DESCRIPTION
		"Displays the number of Service-Unavailable failure response messages
	      generated when rejecting a SIP message due to the server undergoing maintenance or temporary
	      traffic overload."
	::= { ltmSipsessionProfileStatEntry 57 }

ltmSipsessionProfileStatServiceUnavailable503Sent OBJECT-TYPE
	SYNTAX Counter64
	MAX-ACCESS read-only
	STATUS current
	DESCRIPTION
		"Displays the number of Service-Unavailable failure response
	      messages sent when rejecting a SIP message due to the server undergoing maintenance or temporary
	      traffic overload."
	::= { ltmSipsessionProfileStatEntry 58 }

ltmSipsessionProfileStatVersionNotSupported OBJECT-TYPE
	SYNTAX Counter64
	MAX-ACCESS read-only
	STATUS current
	DESCRIPTION
		"Displays the number of Version-Not-Supported failure response messages
	      generated when rejecting a SIP message when the SIP protocol version in the request is not supported
	      by the server."
	::= { ltmSipsessionProfileStatEntry 59 }

ltmSipsessionProfileStatVersionNotSupported505Sent OBJECT-TYPE
	SYNTAX Counter64
	MAX-ACCESS read-only
	STATUS current
	DESCRIPTION
		"Displays the number of Version-Not-Supported failure response
	      messages sent when rejecting a SIP message when the SIP protocol version in the request is not supported
	      by the server."
	::= { ltmSipsessionProfileStatEntry 60 }

--==================================================================
-- Profile_siprouter_stat
--==================================================================
ltmSiprouterProfileStatResetStats OBJECT-TYPE
	SYNTAX INTEGER
	MAX-ACCESS read-write
	STATUS current
	DESCRIPTION
		"The action to reset resettable statistics data in ltmSiprouterProfileStat.
		 Setting this value to 1 will reset statistics data.
		 Note, some statistics data may not be reset including data that are incremental counters."
	::= { ltmSiprouterProfileStat 1 }

ltmSiprouterProfileStatNumber OBJECT-TYPE
	SYNTAX INTEGER
	MAX-ACCESS read-only
	STATUS current
	DESCRIPTION
		"The number of ltmSiprouterProfileStat entries in the table."
	::= { ltmSiprouterProfileStat 2 }

ltmSiprouterProfileStatTable OBJECT-TYPE
	SYNTAX SEQUENCE OF LtmSiprouterProfileStatEntry
	MAX-ACCESS not-accessible
	STATUS current
	DESCRIPTION
		"A table containing statistic information for SIP router profiles."
	::= { ltmSiprouterProfileStat 3 }

ltmSiprouterProfileStatEntry OBJECT-TYPE
	SYNTAX  LtmSiprouterProfileStatEntry
	MAX-ACCESS not-accessible
	STATUS current
	DESCRIPTION
		"Columns in the ltmSiprouterProfileStat Table"
	INDEX {
		ltmSiprouterProfileStatName,
		ltmSiprouterProfileStatVsName
	}
	::= { ltmSiprouterProfileStatTable 1 }

LtmSiprouterProfileStatEntry ::=
	SEQUENCE {
        	ltmSiprouterProfileStatName                               LongDisplayString,
        	ltmSiprouterProfileStatVsName                             LongDisplayString,
        	ltmSiprouterProfileStatTotMessgesIn                       Counter64,
        	ltmSiprouterProfileStatTotMessagesInRetry                 Counter64,
        	ltmSiprouterProfileStatTotMessagesOut                     Counter64,
        	ltmSiprouterProfileStatTotMessagesCannotReturn            Counter64,
        	ltmSiprouterProfileStatTotMessagesRouted                  Counter64,
        	ltmSiprouterProfileStatTotMessagesUnroutable              Counter64,
        	ltmSiprouterProfileStatTotMessagesDropped                 Counter64,
        	ltmSiprouterProfileStatTotMessagesQueueFull               Counter64,
        	ltmSiprouterProfileStatTotMessagesNoConnection            Counter64,
        	ltmSiprouterProfileStatTotMessagesConnectionClosed        Counter64,
        	ltmSiprouterProfileStatTotMessagesInternalError           Counter64,
        	ltmSiprouterProfileStatTotMessagesPersistInUse            Counter64,
        	ltmSiprouterProfileStatTotMessagesStandbyDropped          Counter64,
        	ltmSiprouterProfileStatTotMessagesMaxRetries              Counter64,
        	ltmSiprouterProfileStatTotMessagesInCloned                Counter64,
        	ltmSiprouterProfileStatTotMessagesReturned                Counter64,
        	ltmSiprouterProfileStatTotPayloadBytesIn                  Counter64,
        	ltmSiprouterProfileStatTotPayloadBytesOut                 Counter64,
        	ltmSiprouterProfileStatCurIncomingStreams                 Counter64,
        	ltmSiprouterProfileStatCurOutgoingStreams                 Counter64,
        	ltmSiprouterProfileStatTotIncomingStreams                 Counter64,
        	ltmSiprouterProfileStatTotOutgoingStreams                 Counter64,
        	ltmSiprouterProfileStatTotFailedOutgoingStreams           Counter64,
        	ltmSiprouterProfileStatCurIncomingConnections             Counter64,
        	ltmSiprouterProfileStatCurOutgoingConnections             Counter64,
        	ltmSiprouterProfileStatCurAutoInitOutgoingConns           Counter64,
        	ltmSiprouterProfileStatTotIncomingConnections             Counter64,
        	ltmSiprouterProfileStatTotOutgoingConnections             Counter64,
        	ltmSiprouterProfileStatTotAutoInitOutgoingConns           Counter64,
        	ltmSiprouterProfileStatTotFailedOutgoingConnections       Counter64,
        	ltmSiprouterProfileStatTotFailAutoInitOutgoingConns       Counter64,
        	ltmSiprouterProfileStatCurPassthruConnections             Counter64,
        	ltmSiprouterProfileStatTotPassthruConnections             Counter64,
        	ltmSiprouterProfileStatTotFailedPassthruConnections       Counter64,
        	ltmSiprouterProfileStatTotPassthruBytes                   Counter64,
        	ltmSiprouterProfileStatCurrPendingCalls                   Gauge,
        	ltmSiprouterProfileStatCurrActiveCalls                    Gauge,
        	ltmSiprouterProfileStatTotSuccessfulCalls                 Gauge,
        	ltmSiprouterProfileStatTotRejectedCalls                   Gauge,
        	ltmSiprouterProfileStatTotCancelledCalls                  Gauge,
        	ltmSiprouterProfileStatActiveRegistrations                Gauge,
        	ltmSiprouterProfileStatRejectedRegistrations              Gauge
	}

ltmSiprouterProfileStatName OBJECT-TYPE
	SYNTAX LongDisplayString
	MAX-ACCESS read-only
	STATUS current
	DESCRIPTION
		"The Name of the SIP router profile."
	::= { ltmSiprouterProfileStatEntry 1 }

ltmSiprouterProfileStatVsName OBJECT-TYPE
	SYNTAX LongDisplayString
	MAX-ACCESS read-only
	STATUS current
	DESCRIPTION
		"The Name of the virtual server."
	::= { ltmSiprouterProfileStatEntry 2 }

ltmSiprouterProfileStatTotMessgesIn OBJECT-TYPE
	SYNTAX Counter64
	MAX-ACCESS read-only
	STATUS current
	DESCRIPTION
		"Displays the number of messages received for forwarding."
	::= { ltmSiprouterProfileStatEntry 3 }

ltmSiprouterProfileStatTotMessagesInRetry OBJECT-TYPE
	SYNTAX Counter64
	MAX-ACCESS read-only
	STATUS current
	DESCRIPTION
		"Displays the number of retry messages received for forwarding."
	::= { ltmSiprouterProfileStatEntry 4 }

ltmSiprouterProfileStatTotMessagesOut OBJECT-TYPE
	SYNTAX Counter64
	MAX-ACCESS read-only
	STATUS current
	DESCRIPTION
		"Displays the number of messages forwarded or returned to the originator."
	::= { ltmSiprouterProfileStatEntry 5 }

ltmSiprouterProfileStatTotMessagesCannotReturn OBJECT-TYPE
	SYNTAX Counter64
	MAX-ACCESS read-only
	STATUS current
	DESCRIPTION
		"Displays the number of messages which routing failed and could not be returned to the originator."
	::= { ltmSiprouterProfileStatEntry 6 }

ltmSiprouterProfileStatTotMessagesRouted OBJECT-TYPE
	SYNTAX Counter64
	MAX-ACCESS read-only
	STATUS current
	DESCRIPTION
		"Displays the number of messages where a route was successfully found."
	::= { ltmSiprouterProfileStatEntry 7 }

ltmSiprouterProfileStatTotMessagesUnroutable OBJECT-TYPE
	SYNTAX Counter64
	MAX-ACCESS read-only
	STATUS current
	DESCRIPTION
		"Displays the number of messages where no route was found."
	::= { ltmSiprouterProfileStatEntry 8 }

ltmSiprouterProfileStatTotMessagesDropped OBJECT-TYPE
	SYNTAX Counter64
	MAX-ACCESS read-only
	STATUS current
	DESCRIPTION
		"Displays the number of messages dropped via an iRule."
	::= { ltmSiprouterProfileStatEntry 9 }

ltmSiprouterProfileStatTotMessagesQueueFull OBJECT-TYPE
	SYNTAX Counter64
	MAX-ACCESS read-only
	STATUS current
	DESCRIPTION
		"Displays the number of messages which were routed but the outgoing
	      queue for the destination was full."
	::= { ltmSiprouterProfileStatEntry 10 }

ltmSiprouterProfileStatTotMessagesNoConnection OBJECT-TYPE
	SYNTAX Counter64
	MAX-ACCESS read-only
	STATUS current
	DESCRIPTION
		"Displays the number of messages which were routed to a connection which was closed before the
	      message could be delivered."
	::= { ltmSiprouterProfileStatEntry 11 }

ltmSiprouterProfileStatTotMessagesConnectionClosed OBJECT-TYPE
	SYNTAX Counter64
	MAX-ACCESS read-only
	STATUS current
	DESCRIPTION
		"Displays the number of messages which were pending delivery when the connection closed."
	::= { ltmSiprouterProfileStatEntry 12 }

ltmSiprouterProfileStatTotMessagesInternalError OBJECT-TYPE
	SYNTAX Counter64
	MAX-ACCESS read-only
	STATUS current
	DESCRIPTION
		"Displays the number of messages which were not routed due to an internal error ."
	::= { ltmSiprouterProfileStatEntry 13 }

ltmSiprouterProfileStatTotMessagesPersistInUse OBJECT-TYPE
	SYNTAX Counter64
	MAX-ACCESS read-only
	STATUS current
	DESCRIPTION
		"Displays the number of messages which after routing failed to add a persistence entry because it
	      was already in use."
	::= { ltmSiprouterProfileStatEntry 14 }

ltmSiprouterProfileStatTotMessagesStandbyDropped OBJECT-TYPE
	SYNTAX Counter64
	MAX-ACCESS read-only
	STATUS current
	DESCRIPTION
		"Displays the number of messages which were dropped on the
	      standby device."
	::= { ltmSiprouterProfileStatEntry 15 }

ltmSiprouterProfileStatTotMessagesMaxRetries OBJECT-TYPE
	SYNTAX Counter64
	MAX-ACCESS read-only
	STATUS current
	DESCRIPTION
		"Displays the number of messages returned to the originator because the latest attempt to retry
	      routing exceeded the configured max retry count."
	::= { ltmSiprouterProfileStatEntry 16 }

ltmSiprouterProfileStatTotMessagesInCloned OBJECT-TYPE
	SYNTAX Counter64
	MAX-ACCESS read-only
	STATUS current
	DESCRIPTION
		"Displays the total number of messages cloned per route."
	::= { ltmSiprouterProfileStatEntry 17 }

ltmSiprouterProfileStatTotMessagesReturned OBJECT-TYPE
	SYNTAX Counter64
	MAX-ACCESS read-only
	STATUS current
	DESCRIPTION
		"Displays the number of messages returned."
	::= { ltmSiprouterProfileStatEntry 18 }

ltmSiprouterProfileStatTotPayloadBytesIn OBJECT-TYPE
	SYNTAX Counter64
	MAX-ACCESS read-only
	STATUS current
	DESCRIPTION
		"Displays the number of bytes of payload received."
	::= { ltmSiprouterProfileStatEntry 19 }

ltmSiprouterProfileStatTotPayloadBytesOut OBJECT-TYPE
	SYNTAX Counter64
	MAX-ACCESS read-only
	STATUS current
	DESCRIPTION
		"Displays the number of bytes of payload sent."
	::= { ltmSiprouterProfileStatEntry 20 }

ltmSiprouterProfileStatCurIncomingStreams OBJECT-TYPE
	SYNTAX Counter64
	MAX-ACCESS read-only
	STATUS current
	DESCRIPTION
		"Displays the number of active incoming streams."
	::= { ltmSiprouterProfileStatEntry 21 }

ltmSiprouterProfileStatCurOutgoingStreams OBJECT-TYPE
	SYNTAX Counter64
	MAX-ACCESS read-only
	STATUS current
	DESCRIPTION
		"Displays the number of active outgoing streams."
	::= { ltmSiprouterProfileStatEntry 22 }

ltmSiprouterProfileStatTotIncomingStreams OBJECT-TYPE
	SYNTAX Counter64
	MAX-ACCESS read-only
	STATUS current
	DESCRIPTION
		"Displays the total number of incoming streams since TMM restart or stats reset."
	::= { ltmSiprouterProfileStatEntry 23 }

ltmSiprouterProfileStatTotOutgoingStreams OBJECT-TYPE
	SYNTAX Counter64
	MAX-ACCESS read-only
	STATUS current
	DESCRIPTION
		"Displays the total number of outgoing streams since TMM restart or stats reset."
	::= { ltmSiprouterProfileStatEntry 24 }

ltmSiprouterProfileStatTotFailedOutgoingStreams OBJECT-TYPE
	SYNTAX Counter64
	MAX-ACCESS read-only
	STATUS current
	DESCRIPTION
		"Displays the total number of failed outgoing streams since TMM restart or stats reset."
	::= { ltmSiprouterProfileStatEntry 25 }

ltmSiprouterProfileStatCurIncomingConnections OBJECT-TYPE
	SYNTAX Counter64
	MAX-ACCESS read-only
	STATUS current
	DESCRIPTION
		"Displays the number of active incoming connections."
	::= { ltmSiprouterProfileStatEntry 26 }

ltmSiprouterProfileStatCurOutgoingConnections OBJECT-TYPE
	SYNTAX Counter64
	MAX-ACCESS read-only
	STATUS current
	DESCRIPTION
		"Displays the number of active outgoing connections (including outgoing connections created by
	      auto-initialization)."
	::= { ltmSiprouterProfileStatEntry 27 }

ltmSiprouterProfileStatCurAutoInitOutgoingConns OBJECT-TYPE
	SYNTAX Counter64
	MAX-ACCESS read-only
	STATUS current
	DESCRIPTION
		"Displays the number of active outgoing connections created by auto-initialization."
	::= { ltmSiprouterProfileStatEntry 28 }

ltmSiprouterProfileStatTotIncomingConnections OBJECT-TYPE
	SYNTAX Counter64
	MAX-ACCESS read-only
	STATUS current
	DESCRIPTION
		"Displays the total number of incoming connections created since TMM restart or stats reset."
	::= { ltmSiprouterProfileStatEntry 29 }

ltmSiprouterProfileStatTotOutgoingConnections OBJECT-TYPE
	SYNTAX Counter64
	MAX-ACCESS read-only
	STATUS current
	DESCRIPTION
		"Displays the total number of outgoing connections created since TMM restart or stats reset
	      (including outgoing connections created by auto-initialization)."
	::= { ltmSiprouterProfileStatEntry 30 }

ltmSiprouterProfileStatTotAutoInitOutgoingConns OBJECT-TYPE
	SYNTAX Counter64
	MAX-ACCESS read-only
	STATUS current
	DESCRIPTION
		"Displays the total number of outgoing connections created by auto-initialization since
	      TMM restart or stats reset."
	::= { ltmSiprouterProfileStatEntry 31 }

ltmSiprouterProfileStatTotFailedOutgoingConnections OBJECT-TYPE
	SYNTAX Counter64
	MAX-ACCESS read-only
	STATUS current
	DESCRIPTION
		"Displays the total number of outgoing connections that failed to be established."
	::= { ltmSiprouterProfileStatEntry 32 }

ltmSiprouterProfileStatTotFailAutoInitOutgoingConns OBJECT-TYPE
	SYNTAX Counter64
	MAX-ACCESS read-only
	STATUS current
	DESCRIPTION
		"Displays the total number of outgoing connections that failed to be established by
	      auto-initalization."
	::= { ltmSiprouterProfileStatEntry 33 }

ltmSiprouterProfileStatCurPassthruConnections OBJECT-TYPE
	SYNTAX Counter64
	MAX-ACCESS read-only
	STATUS current
	DESCRIPTION
		"Displays the number of active pass through connections."
	::= { ltmSiprouterProfileStatEntry 34 }

ltmSiprouterProfileStatTotPassthruConnections OBJECT-TYPE
	SYNTAX Counter64
	MAX-ACCESS read-only
	STATUS current
	DESCRIPTION
		"Displays the total number of pass through connections since TMM restart or stats reset."
	::= { ltmSiprouterProfileStatEntry 35 }

ltmSiprouterProfileStatTotFailedPassthruConnections OBJECT-TYPE
	SYNTAX Counter64
	MAX-ACCESS read-only
	STATUS current
	DESCRIPTION
		"Displays the total number of failed pass through connections since TMM restart or stats reset."
	::= { ltmSiprouterProfileStatEntry 36 }

ltmSiprouterProfileStatTotPassthruBytes OBJECT-TYPE
	SYNTAX Counter64
	MAX-ACCESS read-only
	STATUS current
	DESCRIPTION
		"Displays the number of pass through bytes."
	::= { ltmSiprouterProfileStatEntry 37 }

ltmSiprouterProfileStatCurrPendingCalls OBJECT-TYPE
	SYNTAX Gauge
	MAX-ACCESS read-only
	STATUS current
	DESCRIPTION
		"Displays the current number of pending calls."
	::= { ltmSiprouterProfileStatEntry 38 }

ltmSiprouterProfileStatCurrActiveCalls OBJECT-TYPE
	SYNTAX Gauge
	MAX-ACCESS read-only
	STATUS current
	DESCRIPTION
		"Displays the current number of active calls."
	::= { ltmSiprouterProfileStatEntry 39 }

ltmSiprouterProfileStatTotSuccessfulCalls OBJECT-TYPE
	SYNTAX Gauge
	MAX-ACCESS read-only
	STATUS current
	DESCRIPTION
		"Displays the total number of total successful calls."
	::= { ltmSiprouterProfileStatEntry 40 }

ltmSiprouterProfileStatTotRejectedCalls OBJECT-TYPE
	SYNTAX Gauge
	MAX-ACCESS read-only
	STATUS current
	DESCRIPTION
		"Displays the total number of rejected calls."
	::= { ltmSiprouterProfileStatEntry 41 }

ltmSiprouterProfileStatTotCancelledCalls OBJECT-TYPE
	SYNTAX Gauge
	MAX-ACCESS read-only
	STATUS current
	DESCRIPTION
		"Displays the total number of cancelled calls."
	::= { ltmSiprouterProfileStatEntry 42 }

ltmSiprouterProfileStatActiveRegistrations OBJECT-TYPE
	SYNTAX Gauge
	MAX-ACCESS read-only
	STATUS current
	DESCRIPTION
		"Displays the total number of active registrations."
	::= { ltmSiprouterProfileStatEntry 43 }

ltmSiprouterProfileStatRejectedRegistrations OBJECT-TYPE
	SYNTAX Gauge
	MAX-ACCESS read-only
	STATUS current
	DESCRIPTION
		"Displays the total number of rejected registrations."
	::= { ltmSiprouterProfileStatEntry 44 }

--==================================================================
-- Mr_pmbr_sip_session_stat
--==================================================================
ltmMrPmbrSipSessionStatResetStats OBJECT-TYPE
	SYNTAX INTEGER
	MAX-ACCESS read-write
	STATUS current
	DESCRIPTION
		"The action to reset resettable statistics data in ltmMrPmbrSipSessionStat.
		 Setting this value to 1 will reset statistics data.
		 Note, some statistics data may not be reset including data that are incremental counters."
	::= { ltmMrPmbrSipSessionStat 1 }

ltmMrPmbrSipSessionStatNumber OBJECT-TYPE
	SYNTAX INTEGER
	MAX-ACCESS read-only
	STATUS current
	DESCRIPTION
		"The number of ltmMrPmbrSipSessionStat entries in the table."
	::= { ltmMrPmbrSipSessionStat 2 }

ltmMrPmbrSipSessionStatTable OBJECT-TYPE
	SYNTAX SEQUENCE OF LtmMrPmbrSipSessionStatEntry
	MAX-ACCESS not-accessible
	STATUS current
	DESCRIPTION
		"A table containing statistic information for message routing SIP session profiles."
	::= { ltmMrPmbrSipSessionStat 3 }

ltmMrPmbrSipSessionStatEntry OBJECT-TYPE
	SYNTAX  LtmMrPmbrSipSessionStatEntry
	MAX-ACCESS not-accessible
	STATUS current
	DESCRIPTION
		"Columns in the ltmMrPmbrSipSessionStat Table"
	INDEX {
		ltmMrPmbrSipSessionStatRouterInst,
		ltmMrPmbrSipSessionStatMrType,
		ltmMrPmbrSipSessionStatTrName,
		ltmMrPmbrSipSessionStatPool,
		ltmMrPmbrSipSessionStatProfileName,
		ltmMrPmbrSipSessionStatAddrType,
		ltmMrPmbrSipSessionStatAddr,
		ltmMrPmbrSipSessionStatPort
	}
	::= { ltmMrPmbrSipSessionStatTable 1 }

LtmMrPmbrSipSessionStatEntry ::=
	SEQUENCE {
        	ltmMrPmbrSipSessionStatRouterInst                         LongDisplayString,
        	ltmMrPmbrSipSessionStatMrType                             LongDisplayString,
        	ltmMrPmbrSipSessionStatTrName                             LongDisplayString,
        	ltmMrPmbrSipSessionStatPool                               LongDisplayString,
        	ltmMrPmbrSipSessionStatProfileName                        LongDisplayString,
        	ltmMrPmbrSipSessionStatAddrType                           InetAddressType,
        	ltmMrPmbrSipSessionStatAddr                               InetAddress,
        	ltmMrPmbrSipSessionStatPort                               InetPortNumber,
        	ltmMrPmbrSipSessionStatRequests                           Counter64,
        	ltmMrPmbrSipSessionStatResponses                          Counter64,
        	ltmMrPmbrSipSessionStatBadmsgs                            Counter64,
        	ltmMrPmbrSipSessionStatBadmsgsReq                         Counter64,
        	ltmMrPmbrSipSessionStatDrops                              Counter64,
        	ltmMrPmbrSipSessionStatDropsReq                           Counter64,
        	ltmMrPmbrSipSessionStatInvite                             Counter64,
        	ltmMrPmbrSipSessionStatAck                                Counter64,
        	ltmMrPmbrSipSessionStatBye                                Counter64,
        	ltmMrPmbrSipSessionStatCancel                             Counter64,
        	ltmMrPmbrSipSessionStatOptions                            Counter64,
        	ltmMrPmbrSipSessionStatRegisterReq                        Counter64,
        	ltmMrPmbrSipSessionStatPrack                              Counter64,
        	ltmMrPmbrSipSessionStatSubscribe                          Counter64,
        	ltmMrPmbrSipSessionStatNotify                             Counter64,
        	ltmMrPmbrSipSessionStatPublish                            Counter64,
        	ltmMrPmbrSipSessionStatInfo                               Counter64,
        	ltmMrPmbrSipSessionStatRefer                              Counter64,
        	ltmMrPmbrSipSessionStatMessage                            Counter64,
        	ltmMrPmbrSipSessionStatUpdateReq                          Counter64,
        	ltmMrPmbrSipSessionStatService                            Counter64,
        	ltmMrPmbrSipSessionStatBenotify                           Counter64,
        	ltmMrPmbrSipSessionStatNegotiate                          Counter64,
        	ltmMrPmbrSipSessionStatOther                              Counter64,
        	ltmMrPmbrSipSessionStatProvisional                        Counter64,
        	ltmMrPmbrSipSessionStatSuccessful                         Counter64,
        	ltmMrPmbrSipSessionStatRedirection                        Counter64,
        	ltmMrPmbrSipSessionStatClientFailures                     Counter64,
        	ltmMrPmbrSipSessionStatServerFailures                     Counter64,
        	ltmMrPmbrSipSessionStatGlobalFailures                     Counter64,
        	ltmMrPmbrSipSessionStatBadRequest                         Counter64,
        	ltmMrPmbrSipSessionStatBadRequest400Sent                  Counter64,
        	ltmMrPmbrSipSessionStatNotFound                           Counter64,
        	ltmMrPmbrSipSessionStatNotFound404Sent                    Counter64,
        	ltmMrPmbrSipSessionStatRequestEntityTooLarge              Counter64,
        	ltmMrPmbrSipSessionStatRequestEntityTooLarge413Sent       Counter64,
        	ltmMrPmbrSipSessionStatUnsupportedUriScheme               Counter64,
        	ltmMrPmbrSipSessionStatUnsupportedUriScheme416Sent        Counter64,
        	ltmMrPmbrSipSessionStatTemporarilyUnavailable             Counter64,
        	ltmMrPmbrSipSessionStatTemporarilyUnavailable480Sent      Counter64,
        	ltmMrPmbrSipSessionStatTransactionDoesNotExist            Counter64,
        	ltmMrPmbrSipSessionStatTransactionDoesNotExist481Sent     Counter64,
        	ltmMrPmbrSipSessionStatLoopDetected                       Counter64,
        	ltmMrPmbrSipSessionStatLoopDetected482Sent                Counter64,
        	ltmMrPmbrSipSessionStatTooManyHops                        Counter64,
        	ltmMrPmbrSipSessionStatTooManyHops483Sent                 Counter64,
        	ltmMrPmbrSipSessionStatAddressIncomplete                  Counter64,
        	ltmMrPmbrSipSessionStatAddressIncomplete484Sent           Counter64,
        	ltmMrPmbrSipSessionStatNotAcceptableHere                  Counter64,
        	ltmMrPmbrSipSessionStatNotAcceptableHere488Sent           Counter64,
        	ltmMrPmbrSipSessionStatServerInternalError                Counter64,
        	ltmMrPmbrSipSessionStatServerInternalError500Sent         Counter64,
        	ltmMrPmbrSipSessionStatNotImplemented                     Counter64,
        	ltmMrPmbrSipSessionStatNotImplemented501Sent              Counter64,
        	ltmMrPmbrSipSessionStatServiceUnavailable                 Counter64,
        	ltmMrPmbrSipSessionStatServiceUnavailable503Sent          Counter64,
        	ltmMrPmbrSipSessionStatVersionNotSupported                Counter64,
        	ltmMrPmbrSipSessionStatVersionNotSupported505Sent         Counter64
	}

ltmMrPmbrSipSessionStatRouterInst OBJECT-TYPE
	SYNTAX LongDisplayString
	MAX-ACCESS read-only
	STATUS current
	DESCRIPTION
		"The name of the router instance."
	::= { ltmMrPmbrSipSessionStatEntry 1 }

ltmMrPmbrSipSessionStatMrType OBJECT-TYPE
	SYNTAX LongDisplayString
	MAX-ACCESS read-only
	STATUS current
	DESCRIPTION
		"The type of transport - config or virtual."
	::= { ltmMrPmbrSipSessionStatEntry 2 }

ltmMrPmbrSipSessionStatTrName OBJECT-TYPE
	SYNTAX LongDisplayString
	MAX-ACCESS read-only
	STATUS current
	DESCRIPTION
		"The name of the transport config."
	::= { ltmMrPmbrSipSessionStatEntry 3 }

ltmMrPmbrSipSessionStatPool OBJECT-TYPE
	SYNTAX LongDisplayString
	MAX-ACCESS read-only
	STATUS current
	DESCRIPTION
		"The name of the pool."
	::= { ltmMrPmbrSipSessionStatEntry 4 }

ltmMrPmbrSipSessionStatProfileName OBJECT-TYPE
	SYNTAX LongDisplayString
	MAX-ACCESS read-only
	STATUS current
	DESCRIPTION
		"The name of the diameter session profile."
	::= { ltmMrPmbrSipSessionStatEntry 5 }

ltmMrPmbrSipSessionStatAddrType OBJECT-TYPE
	SYNTAX InetAddressType
	MAX-ACCESS read-only
	STATUS current
	DESCRIPTION
		"The IP address type of the pool member address."
	::= { ltmMrPmbrSipSessionStatEntry 6 }

ltmMrPmbrSipSessionStatAddr OBJECT-TYPE
	SYNTAX InetAddress
	MAX-ACCESS read-only
	STATUS current
	DESCRIPTION
		"The IP address of the pool member"
	::= { ltmMrPmbrSipSessionStatEntry 7 }

ltmMrPmbrSipSessionStatPort OBJECT-TYPE
	SYNTAX InetPortNumber
	MAX-ACCESS read-only
	STATUS current
	DESCRIPTION
		"The port number of the specified pool member."
	::= { ltmMrPmbrSipSessionStatEntry 8 }

ltmMrPmbrSipSessionStatRequests OBJECT-TYPE
	SYNTAX Counter64
	MAX-ACCESS read-only
	STATUS current
	DESCRIPTION
		"Displays the number of SIP request messages the system handled."
	::= { ltmMrPmbrSipSessionStatEntry 9 }

ltmMrPmbrSipSessionStatResponses OBJECT-TYPE
	SYNTAX Counter64
	MAX-ACCESS read-only
	STATUS current
	DESCRIPTION
		"Displays the number of SIP response messages the system handled."
	::= { ltmMrPmbrSipSessionStatEntry 10 }

ltmMrPmbrSipSessionStatBadmsgs OBJECT-TYPE
	SYNTAX Counter64
	MAX-ACCESS read-only
	STATUS current
	DESCRIPTION
		"Displays the number of bad SIP messages the system handled."
	::= { ltmMrPmbrSipSessionStatEntry 11 }

ltmMrPmbrSipSessionStatBadmsgsReq OBJECT-TYPE
	SYNTAX Counter64
	MAX-ACCESS read-only
	STATUS current
	DESCRIPTION
		"Displays the number of bad SIP request messages the system handled."
	::= { ltmMrPmbrSipSessionStatEntry 12 }

ltmMrPmbrSipSessionStatDrops OBJECT-TYPE
	SYNTAX Counter64
	MAX-ACCESS read-only
	STATUS current
	DESCRIPTION
		"Displays the total number of SIP messages the system dropped."
	::= { ltmMrPmbrSipSessionStatEntry 13 }

ltmMrPmbrSipSessionStatDropsReq OBJECT-TYPE
	SYNTAX Counter64
	MAX-ACCESS read-only
	STATUS current
	DESCRIPTION
		"Displays the number of SIP request messages the system dropped."
	::= { ltmMrPmbrSipSessionStatEntry 14 }

ltmMrPmbrSipSessionStatInvite OBJECT-TYPE
	SYNTAX Counter64
	MAX-ACCESS read-only
	STATUS current
	DESCRIPTION
		"Displays the number of INVITE SIP request messages the system handled."
	::= { ltmMrPmbrSipSessionStatEntry 15 }

ltmMrPmbrSipSessionStatAck OBJECT-TYPE
	SYNTAX Counter64
	MAX-ACCESS read-only
	STATUS current
	DESCRIPTION
		"Displays the number of ACK SIP request messages the system handled."
	::= { ltmMrPmbrSipSessionStatEntry 16 }

ltmMrPmbrSipSessionStatBye OBJECT-TYPE
	SYNTAX Counter64
	MAX-ACCESS read-only
	STATUS current
	DESCRIPTION
		"Displays the number of BYE SIP request messages the system handled."
	::= { ltmMrPmbrSipSessionStatEntry 17 }

ltmMrPmbrSipSessionStatCancel OBJECT-TYPE
	SYNTAX Counter64
	MAX-ACCESS read-only
	STATUS current
	DESCRIPTION
		"Displays the number of CANCEL SIP request messages the system handled."
	::= { ltmMrPmbrSipSessionStatEntry 18 }

ltmMrPmbrSipSessionStatOptions OBJECT-TYPE
	SYNTAX Counter64
	MAX-ACCESS read-only
	STATUS current
	DESCRIPTION
		"Displays the number of OPTIONS SIP request messages the system handled."
	::= { ltmMrPmbrSipSessionStatEntry 19 }

ltmMrPmbrSipSessionStatRegisterReq OBJECT-TYPE
	SYNTAX Counter64
	MAX-ACCESS read-only
	STATUS current
	DESCRIPTION
		"Displays the number of REGISTER SIP request messages the system handled."
	::= { ltmMrPmbrSipSessionStatEntry 20 }

ltmMrPmbrSipSessionStatPrack OBJECT-TYPE
	SYNTAX Counter64
	MAX-ACCESS read-only
	STATUS current
	DESCRIPTION
		"Displays the number of PRACK SIP request messages the system handled."
	::= { ltmMrPmbrSipSessionStatEntry 21 }

ltmMrPmbrSipSessionStatSubscribe OBJECT-TYPE
	SYNTAX Counter64
	MAX-ACCESS read-only
	STATUS current
	DESCRIPTION
		"Displays the number of SUBSCRIBE SIP request messages the system handled."
	::= { ltmMrPmbrSipSessionStatEntry 22 }

ltmMrPmbrSipSessionStatNotify OBJECT-TYPE
	SYNTAX Counter64
	MAX-ACCESS read-only
	STATUS current
	DESCRIPTION
		"Displays the number of NOTIFY SIP request messages the system handled."
	::= { ltmMrPmbrSipSessionStatEntry 23 }

ltmMrPmbrSipSessionStatPublish OBJECT-TYPE
	SYNTAX Counter64
	MAX-ACCESS read-only
	STATUS current
	DESCRIPTION
		"Displays the number of PUBLISH SIP request messages the system handled."
	::= { ltmMrPmbrSipSessionStatEntry 24 }

ltmMrPmbrSipSessionStatInfo OBJECT-TYPE
	SYNTAX Counter64
	MAX-ACCESS read-only
	STATUS current
	DESCRIPTION
		"Displays the number of INFO SIP request messages the system handled."
	::= { ltmMrPmbrSipSessionStatEntry 25 }

ltmMrPmbrSipSessionStatRefer OBJECT-TYPE
	SYNTAX Counter64
	MAX-ACCESS read-only
	STATUS current
	DESCRIPTION
		"Displays the number of REFER SIP request messages the system handled."
	::= { ltmMrPmbrSipSessionStatEntry 26 }

ltmMrPmbrSipSessionStatMessage OBJECT-TYPE
	SYNTAX Counter64
	MAX-ACCESS read-only
	STATUS current
	DESCRIPTION
		"Displays the number of MESSAGE SIP request messages the system handled."
	::= { ltmMrPmbrSipSessionStatEntry 27 }

ltmMrPmbrSipSessionStatUpdateReq OBJECT-TYPE
	SYNTAX Counter64
	MAX-ACCESS read-only
	STATUS current
	DESCRIPTION
		"Displays the number of UPDATE SIP request messages the system handled."
	::= { ltmMrPmbrSipSessionStatEntry 28 }

ltmMrPmbrSipSessionStatService OBJECT-TYPE
	SYNTAX Counter64
	MAX-ACCESS read-only
	STATUS current
	DESCRIPTION
		"Displays the number of SERVICE SIP request messages the system handled."
	::= { ltmMrPmbrSipSessionStatEntry 29 }

ltmMrPmbrSipSessionStatBenotify OBJECT-TYPE
	SYNTAX Counter64
	MAX-ACCESS read-only
	STATUS current
	DESCRIPTION
		"Displays the number of BENOTIFY SIP request messages the system handled."
	::= { ltmMrPmbrSipSessionStatEntry 30 }

ltmMrPmbrSipSessionStatNegotiate OBJECT-TYPE
	SYNTAX Counter64
	MAX-ACCESS read-only
	STATUS current
	DESCRIPTION
		"Displays the number of NEGOTIATE SIP request messages the system handled."
	::= { ltmMrPmbrSipSessionStatEntry 31 }

ltmMrPmbrSipSessionStatOther OBJECT-TYPE
	SYNTAX Counter64
	MAX-ACCESS read-only
	STATUS current
	DESCRIPTION
		"Displays the number of OTHER SIP request messages the system handled."
	::= { ltmMrPmbrSipSessionStatEntry 32 }

ltmMrPmbrSipSessionStatProvisional OBJECT-TYPE
	SYNTAX Counter64
	MAX-ACCESS read-only
	STATUS current
	DESCRIPTION
		"Displays the number of Provisional SIP response messages the system handled."
	::= { ltmMrPmbrSipSessionStatEntry 33 }

ltmMrPmbrSipSessionStatSuccessful OBJECT-TYPE
	SYNTAX Counter64
	MAX-ACCESS read-only
	STATUS current
	DESCRIPTION
		"Displays the number of Successful SIP response messages the system handled."
	::= { ltmMrPmbrSipSessionStatEntry 34 }

ltmMrPmbrSipSessionStatRedirection OBJECT-TYPE
	SYNTAX Counter64
	MAX-ACCESS read-only
	STATUS current
	DESCRIPTION
		"Displays the number of Redirection SIP response messages the system handled."
	::= { ltmMrPmbrSipSessionStatEntry 35 }

ltmMrPmbrSipSessionStatClientFailures OBJECT-TYPE
	SYNTAX Counter64
	MAX-ACCESS read-only
	STATUS current
	DESCRIPTION
		"Displays the number of Client Failure SIP response messages the system handled."
	::= { ltmMrPmbrSipSessionStatEntry 36 }

ltmMrPmbrSipSessionStatServerFailures OBJECT-TYPE
	SYNTAX Counter64
	MAX-ACCESS read-only
	STATUS current
	DESCRIPTION
		"Displays the number of Server Failure SIP response messages the system handled."
	::= { ltmMrPmbrSipSessionStatEntry 37 }

ltmMrPmbrSipSessionStatGlobalFailures OBJECT-TYPE
	SYNTAX Counter64
	MAX-ACCESS read-only
	STATUS current
	DESCRIPTION
		"Displays the number of Global Failure SIP response messages the system handled."
	::= { ltmMrPmbrSipSessionStatEntry 38 }

ltmMrPmbrSipSessionStatBadRequest OBJECT-TYPE
	SYNTAX Counter64
	MAX-ACCESS read-only
	STATUS current
	DESCRIPTION
		"Displays the number of Bad-Request failure response messages generated when
	      rejecting a SIP message due to a malformed syntax."
	::= { ltmMrPmbrSipSessionStatEntry 39 }

ltmMrPmbrSipSessionStatBadRequest400Sent OBJECT-TYPE
	SYNTAX Counter64
	MAX-ACCESS read-only
	STATUS current
	DESCRIPTION
		"Displays the number of Bad-Request failure response messages sent when
	      rejecting a SIP message due to a malformed syntax."
	::= { ltmMrPmbrSipSessionStatEntry 40 }

ltmMrPmbrSipSessionStatNotFound OBJECT-TYPE
	SYNTAX Counter64
	MAX-ACCESS read-only
	STATUS current
	DESCRIPTION
		"Displays the number of Bad-Request failure response messages generated when rejecting
	      a SIP message when there is no matching user registration entry."
	::= { ltmMrPmbrSipSessionStatEntry 41 }

ltmMrPmbrSipSessionStatNotFound404Sent OBJECT-TYPE
	SYNTAX Counter64
	MAX-ACCESS read-only
	STATUS current
	DESCRIPTION
		"Displays the number of Bad-Request failure response messages sent when
	      rejecting a SIP message when there is no matching user registration entry."
	::= { ltmMrPmbrSipSessionStatEntry 42 }

ltmMrPmbrSipSessionStatRequestEntityTooLarge OBJECT-TYPE
	SYNTAX Counter64
	MAX-ACCESS read-only
	STATUS current
	DESCRIPTION
		"Displays the number of Request-Entity-Too-Large response
	      messages generated when rejecting a SIP message due to some aspect of the message exceeding a
	      configured size limit."
	::= { ltmMrPmbrSipSessionStatEntry 43 }

ltmMrPmbrSipSessionStatRequestEntityTooLarge413Sent OBJECT-TYPE
	SYNTAX Counter64
	MAX-ACCESS read-only
	STATUS current
	DESCRIPTION
		"Displays the number of Request-Entity-Too-Large response
	      messages sent when rejecting a SIP message due to some aspect of the message exceeding a
	      configured size limit."
	::= { ltmMrPmbrSipSessionStatEntry 44 }

ltmMrPmbrSipSessionStatUnsupportedUriScheme OBJECT-TYPE
	SYNTAX Counter64
	MAX-ACCESS read-only
	STATUS current
	DESCRIPTION
		"Displays the number of Unsupported-URI-Scheme responses messages
	      generated when rejecting a SIP message due to malformed URI."
	::= { ltmMrPmbrSipSessionStatEntry 45 }

ltmMrPmbrSipSessionStatUnsupportedUriScheme416Sent OBJECT-TYPE
	SYNTAX Counter64
	MAX-ACCESS read-only
	STATUS current
	DESCRIPTION
		"Displays the number of Unsupported-URI-Scheme responses
	      messages sent when rejecting a SIP message due to malformed URI."
	::= { ltmMrPmbrSipSessionStatEntry 46 }

ltmMrPmbrSipSessionStatTemporarilyUnavailable OBJECT-TYPE
	SYNTAX Counter64
	MAX-ACCESS read-only
	STATUS current
	DESCRIPTION
		"Displays the number of Temporary Unavailable failure response
	      messages generated when rejecting a call when the user is not available at this time."
	::= { ltmMrPmbrSipSessionStatEntry 47 }

ltmMrPmbrSipSessionStatTemporarilyUnavailable480Sent OBJECT-TYPE
	SYNTAX Counter64
	MAX-ACCESS read-only
	STATUS current
	DESCRIPTION
		"Displays the number of Temporary Unavailable failure
	      response messages sent when rejecting a call when the user is not available at this time."
	::= { ltmMrPmbrSipSessionStatEntry 48 }

ltmMrPmbrSipSessionStatTransactionDoesNotExist OBJECT-TYPE
	SYNTAX Counter64
	MAX-ACCESS read-only
	STATUS current
	DESCRIPTION
		"Displays the number of transaction does not exist response
	      message generated when response or request message is not able to be matched to a SIP transaction."
	::= { ltmMrPmbrSipSessionStatEntry 49 }

ltmMrPmbrSipSessionStatTransactionDoesNotExist481Sent OBJECT-TYPE
	SYNTAX Counter64
	MAX-ACCESS read-only
	STATUS current
	DESCRIPTION
		"Displays the number of transaction does not exist response
	      message sent when response or request message is not able to be matched to a SIP transaction."
	::= { ltmMrPmbrSipSessionStatEntry 50 }

ltmMrPmbrSipSessionStatLoopDetected OBJECT-TYPE
	SYNTAX Counter64
	MAX-ACCESS read-only
	STATUS current
	DESCRIPTION
		"Displays the number of Loop-Detected failure response messages generated
	      when rejecting a SIP message due to loop detection."
	::= { ltmMrPmbrSipSessionStatEntry 51 }

ltmMrPmbrSipSessionStatLoopDetected482Sent OBJECT-TYPE
	SYNTAX Counter64
	MAX-ACCESS read-only
	STATUS current
	DESCRIPTION
		"Displays the number of Loop-Detected failure response messages sent
	      when rejecting a SIP message due to loop detection."
	::= { ltmMrPmbrSipSessionStatEntry 52 }

ltmMrPmbrSipSessionStatTooManyHops OBJECT-TYPE
	SYNTAX Counter64
	MAX-ACCESS read-only
	STATUS current
	DESCRIPTION
		"Displays the number of Too-Many-Hops failure response messages generated
	      when rejecting a SIP message as Max-Forwards header has reached value '0'."
	::= { ltmMrPmbrSipSessionStatEntry 53 }

ltmMrPmbrSipSessionStatTooManyHops483Sent OBJECT-TYPE
	SYNTAX Counter64
	MAX-ACCESS read-only
	STATUS current
	DESCRIPTION
		"Displays the number of Too-Many-Hops failure response messages sent
	      when rejecting a SIP message as Max-Forwards header has reached value '0'."
	::= { ltmMrPmbrSipSessionStatEntry 54 }

ltmMrPmbrSipSessionStatAddressIncomplete OBJECT-TYPE
	SYNTAX Counter64
	MAX-ACCESS read-only
	STATUS current
	DESCRIPTION
		"Displays the number of Address-Incomplete failure response
	      messages generated when rejecting a SIP message due to malformed or incomplete request URI."
	::= { ltmMrPmbrSipSessionStatEntry 55 }

ltmMrPmbrSipSessionStatAddressIncomplete484Sent OBJECT-TYPE
	SYNTAX Counter64
	MAX-ACCESS read-only
	STATUS current
	DESCRIPTION
		"Displays the number of Address-Incomplete failure
	      response messages sent when rejecting a SIP message due to malformed or incomplete request URI."
	::= { ltmMrPmbrSipSessionStatEntry 56 }

ltmMrPmbrSipSessionStatNotAcceptableHere OBJECT-TYPE
	SYNTAX Counter64
	MAX-ACCESS read-only
	STATUS current
	DESCRIPTION
		"Displays the number of Not-Acceptable failure response
	      messages generated when rejecting a SIP message containing too many SDP media requests."
	::= { ltmMrPmbrSipSessionStatEntry 57 }

ltmMrPmbrSipSessionStatNotAcceptableHere488Sent OBJECT-TYPE
	SYNTAX Counter64
	MAX-ACCESS read-only
	STATUS current
	DESCRIPTION
		"Displays the number of Not-Acceptable failure response
	      messages sent when rejecting a SIP message containing too many SDP media requests."
	::= { ltmMrPmbrSipSessionStatEntry 58 }

ltmMrPmbrSipSessionStatServerInternalError OBJECT-TYPE
	SYNTAX Counter64
	MAX-ACCESS read-only
	STATUS current
	DESCRIPTION
		"Displays the number of Server-Internal-Error failure response
	      messages generated when rejecting a SIP message due to some unexpected condition and cannot
	      fulfill the request."
	::= { ltmMrPmbrSipSessionStatEntry 59 }

ltmMrPmbrSipSessionStatServerInternalError500Sent OBJECT-TYPE
	SYNTAX Counter64
	MAX-ACCESS read-only
	STATUS current
	DESCRIPTION
		"Displays the number of Server-Internal-Error failure response
	      messages sent when rejecting a SIP message due to some unexpected condition and cannot
	      fulfill the request."
	::= { ltmMrPmbrSipSessionStatEntry 60 }

ltmMrPmbrSipSessionStatNotImplemented OBJECT-TYPE
	SYNTAX Counter64
	MAX-ACCESS read-only
	STATUS current
	DESCRIPTION
		"Displays the number of Not-Implemented failure response messages generated
	      when rejecting a SIP message due to an invalid/unimplemented request method."
	::= { ltmMrPmbrSipSessionStatEntry 61 }

ltmMrPmbrSipSessionStatNotImplemented501Sent OBJECT-TYPE
	SYNTAX Counter64
	MAX-ACCESS read-only
	STATUS current
	DESCRIPTION
		"Displays the number of Not-Implemented failure response messages
	      sent when rejecting a SIP message due to an invalid/unimplemented request method."
	::= { ltmMrPmbrSipSessionStatEntry 62 }

ltmMrPmbrSipSessionStatServiceUnavailable OBJECT-TYPE
	SYNTAX Counter64
	MAX-ACCESS read-only
	STATUS current
	DESCRIPTION
		"Displays the number of Service-Unavailable failure response messages
	      generated when rejecting a SIP message due to the server undergoing maintenance or temporary
	      traffic overload."
	::= { ltmMrPmbrSipSessionStatEntry 63 }

ltmMrPmbrSipSessionStatServiceUnavailable503Sent OBJECT-TYPE
	SYNTAX Counter64
	MAX-ACCESS read-only
	STATUS current
	DESCRIPTION
		"Displays the number of Service-Unavailable failure response
	      messages sent when rejecting a SIP message due to the server undergoing maintenance or temporary
	      traffic overload."
	::= { ltmMrPmbrSipSessionStatEntry 64 }

ltmMrPmbrSipSessionStatVersionNotSupported OBJECT-TYPE
	SYNTAX Counter64
	MAX-ACCESS read-only
	STATUS current
	DESCRIPTION
		"Displays the number of Version-Not-Supported failure response messages
	      generated when rejecting a SIP message when the SIP protocol version in the request is not supported
	      by the server."
	::= { ltmMrPmbrSipSessionStatEntry 65 }

ltmMrPmbrSipSessionStatVersionNotSupported505Sent OBJECT-TYPE
	SYNTAX Counter64
	MAX-ACCESS read-only
	STATUS current
	DESCRIPTION
		"Displays the number of Version-Not-Supported failure response
	      messages sent when rejecting a SIP message when the SIP protocol version in the request is not supported
	      by the server."
	::= { ltmMrPmbrSipSessionStatEntry 66 }

--==================================================================
-- Mr_pmbr_sip_router_stat
--==================================================================
ltmMrPmbrSipRouterStatResetStats OBJECT-TYPE
	SYNTAX INTEGER
	MAX-ACCESS read-write
	STATUS current
	DESCRIPTION
		"The action to reset resettable statistics data in ltmMrPmbrSipRouterStat.
		 Setting this value to 1 will reset statistics data.
		 Note, some statistics data may not be reset including data that are incremental counters."
	::= { ltmMrPmbrSipRouterStat 1 }

ltmMrPmbrSipRouterStatNumber OBJECT-TYPE
	SYNTAX INTEGER
	MAX-ACCESS read-only
	STATUS current
	DESCRIPTION
		"The number of ltmMrPmbrSipRouterStat entries in the table."
	::= { ltmMrPmbrSipRouterStat 2 }

ltmMrPmbrSipRouterStatTable OBJECT-TYPE
	SYNTAX SEQUENCE OF LtmMrPmbrSipRouterStatEntry
	MAX-ACCESS not-accessible
	STATUS current
	DESCRIPTION
		"A table containing statistic information for message routing SIP router profiles."
	::= { ltmMrPmbrSipRouterStat 3 }

ltmMrPmbrSipRouterStatEntry OBJECT-TYPE
	SYNTAX  LtmMrPmbrSipRouterStatEntry
	MAX-ACCESS not-accessible
	STATUS current
	DESCRIPTION
		"Columns in the ltmMrPmbrSipRouterStat Table"
	INDEX {
		ltmMrPmbrSipRouterStatRouterInst,
		ltmMrPmbrSipRouterStatMrType,
		ltmMrPmbrSipRouterStatTrName,
		ltmMrPmbrSipRouterStatPool,
		ltmMrPmbrSipRouterStatAddrType,
		ltmMrPmbrSipRouterStatAddr,
		ltmMrPmbrSipRouterStatPort
	}
	::= { ltmMrPmbrSipRouterStatTable 1 }

LtmMrPmbrSipRouterStatEntry ::=
	SEQUENCE {
        	ltmMrPmbrSipRouterStatRouterInst                          LongDisplayString,
        	ltmMrPmbrSipRouterStatMrType                              LongDisplayString,
        	ltmMrPmbrSipRouterStatTrName                              LongDisplayString,
        	ltmMrPmbrSipRouterStatPool                                LongDisplayString,
        	ltmMrPmbrSipRouterStatAddrType                            InetAddressType,
        	ltmMrPmbrSipRouterStatAddr                                InetAddress,
        	ltmMrPmbrSipRouterStatPort                                InetPortNumber,
        	ltmMrPmbrSipRouterStatTotMessgesIn                        Counter64,
        	ltmMrPmbrSipRouterStatTotMessagesInRetry                  Counter64,
        	ltmMrPmbrSipRouterStatTotMessagesOut                      Counter64,
        	ltmMrPmbrSipRouterStatTotMessagesCannotReturn             Counter64,
        	ltmMrPmbrSipRouterStatTotMessagesRouted                   Counter64,
        	ltmMrPmbrSipRouterStatTotMessagesUnroutable               Counter64,
        	ltmMrPmbrSipRouterStatTotMessagesDropped                  Counter64,
        	ltmMrPmbrSipRouterStatTotMessagesQueueFull                Counter64,
        	ltmMrPmbrSipRouterStatTotMessagesNoConnection             Counter64,
        	ltmMrPmbrSipRouterStatTotMessagesConnectionClosed         Counter64,
        	ltmMrPmbrSipRouterStatTotMessagesInternalError            Counter64,
        	ltmMrPmbrSipRouterStatTotMessagesPersistInUse             Counter64,
        	ltmMrPmbrSipRouterStatTotMessagesStandbyDropped           Counter64,
        	ltmMrPmbrSipRouterStatTotMessagesMaxRetries               Counter64,
        	ltmMrPmbrSipRouterStatTotMessagesInCloned                 Counter64,
        	ltmMrPmbrSipRouterStatTotMessagesReturned                 Counter64,
        	ltmMrPmbrSipRouterStatTotPayloadBytesIn                   Counter64,
        	ltmMrPmbrSipRouterStatTotPayloadBytesOut                  Counter64,
        	ltmMrPmbrSipRouterStatCurIncomingStreams                  Counter64,
        	ltmMrPmbrSipRouterStatCurOutgoingStreams                  Counter64,
        	ltmMrPmbrSipRouterStatTotIncomingStreams                  Counter64,
        	ltmMrPmbrSipRouterStatTotOutgoingStreams                  Counter64,
        	ltmMrPmbrSipRouterStatTotFailedOutgoingStreams            Counter64,
        	ltmMrPmbrSipRouterStatCurIncomingConnections              Counter64,
        	ltmMrPmbrSipRouterStatCurOutgoingConnections              Counter64,
        	ltmMrPmbrSipRouterStatCurAutoInitOutgoingConns            Counter64,
        	ltmMrPmbrSipRouterStatTotIncomingConnections              Counter64,
        	ltmMrPmbrSipRouterStatTotOutgoingConnections              Counter64,
        	ltmMrPmbrSipRouterStatTotAutoInitOutgoingConns            Counter64,
        	ltmMrPmbrSipRouterStatTotFailedOutgoingConnections        Counter64,
        	ltmMrPmbrSipRouterStatTotFailAutoInitOutgoingConns        Counter64,
        	ltmMrPmbrSipRouterStatCurPassthruConnections              Counter64,
        	ltmMrPmbrSipRouterStatTotPassthruConnections              Counter64,
        	ltmMrPmbrSipRouterStatTotFailedPassthruConnections        Counter64,
        	ltmMrPmbrSipRouterStatTotPassthruBytes                    Counter64,
        	ltmMrPmbrSipRouterStatCurrPendingCalls                    Gauge,
        	ltmMrPmbrSipRouterStatCurrActiveCalls                     Gauge,
        	ltmMrPmbrSipRouterStatTotSuccessfulCalls                  Gauge,
        	ltmMrPmbrSipRouterStatTotRejectedCalls                    Gauge,
        	ltmMrPmbrSipRouterStatTotCancelledCalls                   Gauge,
        	ltmMrPmbrSipRouterStatActiveRegistrations                 Gauge,
        	ltmMrPmbrSipRouterStatRejectedRegistrations               Gauge,
        	ltmMrPmbrSipRouterStatMaxRegistrationsPerSubscriber       Gauge,
        	ltmMrPmbrSipRouterStatConcurrentSessionsPerSubscriber     Gauge
	}

ltmMrPmbrSipRouterStatRouterInst OBJECT-TYPE
	SYNTAX LongDisplayString
	MAX-ACCESS read-only
	STATUS current
	DESCRIPTION
		"The name of the router instance."
	::= { ltmMrPmbrSipRouterStatEntry 1 }

ltmMrPmbrSipRouterStatMrType OBJECT-TYPE
	SYNTAX LongDisplayString
	MAX-ACCESS read-only
	STATUS current
	DESCRIPTION
		"The type of transport - config or virtual."
	::= { ltmMrPmbrSipRouterStatEntry 2 }

ltmMrPmbrSipRouterStatTrName OBJECT-TYPE
	SYNTAX LongDisplayString
	MAX-ACCESS read-only
	STATUS current
	DESCRIPTION
		"The name of the transport config."
	::= { ltmMrPmbrSipRouterStatEntry 3 }

ltmMrPmbrSipRouterStatPool OBJECT-TYPE
	SYNTAX LongDisplayString
	MAX-ACCESS read-only
	STATUS current
	DESCRIPTION
		"The name of the pool."
	::= { ltmMrPmbrSipRouterStatEntry 4 }

ltmMrPmbrSipRouterStatAddrType OBJECT-TYPE
	SYNTAX InetAddressType
	MAX-ACCESS read-only
	STATUS current
	DESCRIPTION
		"The IP address type of the pool member address."
	::= { ltmMrPmbrSipRouterStatEntry 5 }

ltmMrPmbrSipRouterStatAddr OBJECT-TYPE
	SYNTAX InetAddress
	MAX-ACCESS read-only
	STATUS current
	DESCRIPTION
		"The IP address of the pool member"
	::= { ltmMrPmbrSipRouterStatEntry 6 }

ltmMrPmbrSipRouterStatPort OBJECT-TYPE
	SYNTAX InetPortNumber
	MAX-ACCESS read-only
	STATUS current
	DESCRIPTION
		"The port number of the specified pool member."
	::= { ltmMrPmbrSipRouterStatEntry 7 }

ltmMrPmbrSipRouterStatTotMessgesIn OBJECT-TYPE
	SYNTAX Counter64
	MAX-ACCESS read-only
	STATUS current
	DESCRIPTION
		"Displays the number of messages received for forwarding."
	::= { ltmMrPmbrSipRouterStatEntry 8 }

ltmMrPmbrSipRouterStatTotMessagesInRetry OBJECT-TYPE
	SYNTAX Counter64
	MAX-ACCESS read-only
	STATUS current
	DESCRIPTION
		"Displays the number of retry messages received for forwarding."
	::= { ltmMrPmbrSipRouterStatEntry 9 }

ltmMrPmbrSipRouterStatTotMessagesOut OBJECT-TYPE
	SYNTAX Counter64
	MAX-ACCESS read-only
	STATUS current
	DESCRIPTION
		"Displays the number of messages forwarded or returned to the originator."
	::= { ltmMrPmbrSipRouterStatEntry 10 }

ltmMrPmbrSipRouterStatTotMessagesCannotReturn OBJECT-TYPE
	SYNTAX Counter64
	MAX-ACCESS read-only
	STATUS current
	DESCRIPTION
		"Displays the number of messages which routing failed and could not be returned to the originator."
	::= { ltmMrPmbrSipRouterStatEntry 11 }

ltmMrPmbrSipRouterStatTotMessagesRouted OBJECT-TYPE
	SYNTAX Counter64
	MAX-ACCESS read-only
	STATUS current
	DESCRIPTION
		"Displays the number of messages where a route was successfully found."
	::= { ltmMrPmbrSipRouterStatEntry 12 }

ltmMrPmbrSipRouterStatTotMessagesUnroutable OBJECT-TYPE
	SYNTAX Counter64
	MAX-ACCESS read-only
	STATUS current
	DESCRIPTION
		"Displays the number of messages where no route was found."
	::= { ltmMrPmbrSipRouterStatEntry 13 }

ltmMrPmbrSipRouterStatTotMessagesDropped OBJECT-TYPE
	SYNTAX Counter64
	MAX-ACCESS read-only
	STATUS current
	DESCRIPTION
		"Displays the number of messages dropped via an iRule."
	::= { ltmMrPmbrSipRouterStatEntry 14 }

ltmMrPmbrSipRouterStatTotMessagesQueueFull OBJECT-TYPE
	SYNTAX Counter64
	MAX-ACCESS read-only
	STATUS current
	DESCRIPTION
		"Displays the number of messages which were routed but the outgoing
	      queue for the destination was full."
	::= { ltmMrPmbrSipRouterStatEntry 15 }

ltmMrPmbrSipRouterStatTotMessagesNoConnection OBJECT-TYPE
	SYNTAX Counter64
	MAX-ACCESS read-only
	STATUS current
	DESCRIPTION
		"Displays the number of messages which were routed to a connection which was closed before the
	      message could be delivered."
	::= { ltmMrPmbrSipRouterStatEntry 16 }

ltmMrPmbrSipRouterStatTotMessagesConnectionClosed OBJECT-TYPE
	SYNTAX Counter64
	MAX-ACCESS read-only
	STATUS current
	DESCRIPTION
		"Displays the number of messages which were pending delivery when the connection closed."
	::= { ltmMrPmbrSipRouterStatEntry 17 }

ltmMrPmbrSipRouterStatTotMessagesInternalError OBJECT-TYPE
	SYNTAX Counter64
	MAX-ACCESS read-only
	STATUS current
	DESCRIPTION
		"Displays the number of messages which were not routed due to an internal error ."
	::= { ltmMrPmbrSipRouterStatEntry 18 }

ltmMrPmbrSipRouterStatTotMessagesPersistInUse OBJECT-TYPE
	SYNTAX Counter64
	MAX-ACCESS read-only
	STATUS current
	DESCRIPTION
		"Displays the number of messages which after routing failed to add a persistence entry because it
	      was already in use."
	::= { ltmMrPmbrSipRouterStatEntry 19 }

ltmMrPmbrSipRouterStatTotMessagesStandbyDropped OBJECT-TYPE
	SYNTAX Counter64
	MAX-ACCESS read-only
	STATUS current
	DESCRIPTION
		"Displays the number of messages which were dropped on the
	      standby device."
	::= { ltmMrPmbrSipRouterStatEntry 20 }

ltmMrPmbrSipRouterStatTotMessagesMaxRetries OBJECT-TYPE
	SYNTAX Counter64
	MAX-ACCESS read-only
	STATUS current
	DESCRIPTION
		"Displays the number of messages returned to the originator because the latest attempt to retry
	      routing exceeded the configured max retry count."
	::= { ltmMrPmbrSipRouterStatEntry 21 }

ltmMrPmbrSipRouterStatTotMessagesInCloned OBJECT-TYPE
	SYNTAX Counter64
	MAX-ACCESS read-only
	STATUS current
	DESCRIPTION
		"Displays the total number of messages cloned per route."
	::= { ltmMrPmbrSipRouterStatEntry 22 }

ltmMrPmbrSipRouterStatTotMessagesReturned OBJECT-TYPE
	SYNTAX Counter64
	MAX-ACCESS read-only
	STATUS current
	DESCRIPTION
		"Displays the number of messages returned."
	::= { ltmMrPmbrSipRouterStatEntry 23 }

ltmMrPmbrSipRouterStatTotPayloadBytesIn OBJECT-TYPE
	SYNTAX Counter64
	MAX-ACCESS read-only
	STATUS current
	DESCRIPTION
		"Displays the number of bytes of payload received."
	::= { ltmMrPmbrSipRouterStatEntry 24 }

ltmMrPmbrSipRouterStatTotPayloadBytesOut OBJECT-TYPE
	SYNTAX Counter64
	MAX-ACCESS read-only
	STATUS current
	DESCRIPTION
		"Displays the number of bytes of payload sent."
	::= { ltmMrPmbrSipRouterStatEntry 25 }

ltmMrPmbrSipRouterStatCurIncomingStreams OBJECT-TYPE
	SYNTAX Counter64
	MAX-ACCESS read-only
	STATUS current
	DESCRIPTION
		"Displays the number of active incoming streams."
	::= { ltmMrPmbrSipRouterStatEntry 26 }

ltmMrPmbrSipRouterStatCurOutgoingStreams OBJECT-TYPE
	SYNTAX Counter64
	MAX-ACCESS read-only
	STATUS current
	DESCRIPTION
		"Displays the number of active outgoing streams."
	::= { ltmMrPmbrSipRouterStatEntry 27 }

ltmMrPmbrSipRouterStatTotIncomingStreams OBJECT-TYPE
	SYNTAX Counter64
	MAX-ACCESS read-only
	STATUS current
	DESCRIPTION
		"Displays the total number of incoming streams since TMM restart or stats reset."
	::= { ltmMrPmbrSipRouterStatEntry 28 }

ltmMrPmbrSipRouterStatTotOutgoingStreams OBJECT-TYPE
	SYNTAX Counter64
	MAX-ACCESS read-only
	STATUS current
	DESCRIPTION
		"Displays the total number of outgoing streams since TMM restart or stats reset."
	::= { ltmMrPmbrSipRouterStatEntry 29 }

ltmMrPmbrSipRouterStatTotFailedOutgoingStreams OBJECT-TYPE
	SYNTAX Counter64
	MAX-ACCESS read-only
	STATUS current
	DESCRIPTION
		"Displays the total number of failed outgoing streams since TMM restart or stats reset."
	::= { ltmMrPmbrSipRouterStatEntry 30 }

ltmMrPmbrSipRouterStatCurIncomingConnections OBJECT-TYPE
	SYNTAX Counter64
	MAX-ACCESS read-only
	STATUS current
	DESCRIPTION
		"Displays the number of active incoming connections."
	::= { ltmMrPmbrSipRouterStatEntry 31 }

ltmMrPmbrSipRouterStatCurOutgoingConnections OBJECT-TYPE
	SYNTAX Counter64
	MAX-ACCESS read-only
	STATUS current
	DESCRIPTION
		"Displays the number of active outgoing connections (including outgoing connections created by
	      auto-initialization)."
	::= { ltmMrPmbrSipRouterStatEntry 32 }

ltmMrPmbrSipRouterStatCurAutoInitOutgoingConns OBJECT-TYPE
	SYNTAX Counter64
	MAX-ACCESS read-only
	STATUS current
	DESCRIPTION
		"Displays the number of active outgoing connections created by auto-initialization."
	::= { ltmMrPmbrSipRouterStatEntry 33 }

ltmMrPmbrSipRouterStatTotIncomingConnections OBJECT-TYPE
	SYNTAX Counter64
	MAX-ACCESS read-only
	STATUS current
	DESCRIPTION
		"Displays the total number of incoming connections created since TMM restart or stats reset."
	::= { ltmMrPmbrSipRouterStatEntry 34 }

ltmMrPmbrSipRouterStatTotOutgoingConnections OBJECT-TYPE
	SYNTAX Counter64
	MAX-ACCESS read-only
	STATUS current
	DESCRIPTION
		"Displays the total number of outgoing connections created since TMM restart or stats reset
	      (including outgoing connections created by auto-initialization)."
	::= { ltmMrPmbrSipRouterStatEntry 35 }

ltmMrPmbrSipRouterStatTotAutoInitOutgoingConns OBJECT-TYPE
	SYNTAX Counter64
	MAX-ACCESS read-only
	STATUS current
	DESCRIPTION
		"Displays the total number of outgoing connections created by auto-initialization since
	      TMM restart or stats reset."
	::= { ltmMrPmbrSipRouterStatEntry 36 }

ltmMrPmbrSipRouterStatTotFailedOutgoingConnections OBJECT-TYPE
	SYNTAX Counter64
	MAX-ACCESS read-only
	STATUS current
	DESCRIPTION
		"Displays the total number of outgoing connections that failed to be established."
	::= { ltmMrPmbrSipRouterStatEntry 37 }

ltmMrPmbrSipRouterStatTotFailAutoInitOutgoingConns OBJECT-TYPE
	SYNTAX Counter64
	MAX-ACCESS read-only
	STATUS current
	DESCRIPTION
		"Displays the total number of outgoing connections that failed to be established by
	      auto-initalization."
	::= { ltmMrPmbrSipRouterStatEntry 38 }

ltmMrPmbrSipRouterStatCurPassthruConnections OBJECT-TYPE
	SYNTAX Counter64
	MAX-ACCESS read-only
	STATUS current
	DESCRIPTION
		"Displays the number of active pass through connections."
	::= { ltmMrPmbrSipRouterStatEntry 39 }

ltmMrPmbrSipRouterStatTotPassthruConnections OBJECT-TYPE
	SYNTAX Counter64
	MAX-ACCESS read-only
	STATUS current
	DESCRIPTION
		"Displays the total number of pass through connections since TMM restart or stats reset."
	::= { ltmMrPmbrSipRouterStatEntry 40 }

ltmMrPmbrSipRouterStatTotFailedPassthruConnections OBJECT-TYPE
	SYNTAX Counter64
	MAX-ACCESS read-only
	STATUS current
	DESCRIPTION
		"Displays the total number of failed pass through connections since TMM restart or stats reset."
	::= { ltmMrPmbrSipRouterStatEntry 41 }

ltmMrPmbrSipRouterStatTotPassthruBytes OBJECT-TYPE
	SYNTAX Counter64
	MAX-ACCESS read-only
	STATUS current
	DESCRIPTION
		"Displays the number of pass through bytes."
	::= { ltmMrPmbrSipRouterStatEntry 42 }

ltmMrPmbrSipRouterStatCurrPendingCalls OBJECT-TYPE
	SYNTAX Gauge
	MAX-ACCESS read-only
	STATUS current
	DESCRIPTION
		"Displays the current number of pending calls."
	::= { ltmMrPmbrSipRouterStatEntry 43 }

ltmMrPmbrSipRouterStatCurrActiveCalls OBJECT-TYPE
	SYNTAX Gauge
	MAX-ACCESS read-only
	STATUS current
	DESCRIPTION
		"Displays the current number of active calls."
	::= { ltmMrPmbrSipRouterStatEntry 44 }

ltmMrPmbrSipRouterStatTotSuccessfulCalls OBJECT-TYPE
	SYNTAX Gauge
	MAX-ACCESS read-only
	STATUS current
	DESCRIPTION
		"Displays the total number of total successful calls."
	::= { ltmMrPmbrSipRouterStatEntry 45 }

ltmMrPmbrSipRouterStatTotRejectedCalls OBJECT-TYPE
	SYNTAX Gauge
	MAX-ACCESS read-only
	STATUS current
	DESCRIPTION
		"Displays the total number of rejected calls."
	::= { ltmMrPmbrSipRouterStatEntry 46 }

ltmMrPmbrSipRouterStatTotCancelledCalls OBJECT-TYPE
	SYNTAX Gauge
	MAX-ACCESS read-only
	STATUS current
	DESCRIPTION
		"Displays the total number of cancelled calls."
	::= { ltmMrPmbrSipRouterStatEntry 47 }

ltmMrPmbrSipRouterStatActiveRegistrations OBJECT-TYPE
	SYNTAX Gauge
	MAX-ACCESS read-only
	STATUS current
	DESCRIPTION
		"Displays the total number of active registrations."
	::= { ltmMrPmbrSipRouterStatEntry 48 }

ltmMrPmbrSipRouterStatRejectedRegistrations OBJECT-TYPE
	SYNTAX Gauge
	MAX-ACCESS read-only
	STATUS current
	DESCRIPTION
		"Displays the total number of rejected registrations."
	::= { ltmMrPmbrSipRouterStatEntry 49 }

ltmMrPmbrSipRouterStatMaxRegistrationsPerSubscriber OBJECT-TYPE
	SYNTAX Gauge
	MAX-ACCESS read-only
	STATUS current
	DESCRIPTION
		"Displays the maximum number of registrations per subscriber."
	::= { ltmMrPmbrSipRouterStatEntry 50 }

ltmMrPmbrSipRouterStatConcurrentSessionsPerSubscriber OBJECT-TYPE
	SYNTAX Gauge
	MAX-ACCESS read-only
	STATUS current
	DESCRIPTION
		"Displays the number of concurrent sessions per subscriber."
	::= { ltmMrPmbrSipRouterStatEntry 51 }

--==================================================================
-- Profile_serverssl_c3d_cert_extension_custom_oids
--==================================================================
ltmServerSslProfileC3dCertExtensionCustomOidsNumber OBJECT-TYPE
	SYNTAX INTEGER
	MAX-ACCESS read-only
	STATUS current
	DESCRIPTION
		"The number of ltmServerSslProfileC3dCertExtensionCustomOids entries in the table."
	::= { ltmServerSslProfileC3dCertExtensionCustomOids 1 }

ltmServerSslProfileC3dCertExtensionCustomOidsTable OBJECT-TYPE
	SYNTAX SEQUENCE OF LtmServerSslProfileC3dCertExtensionCustomOidsEntry
	MAX-ACCESS not-accessible
	STATUS current
	DESCRIPTION
		"A table containing the custom extension OIDs information of the client
	         certificates to be included in the generated certificates of server-ssl profile."
	::= { ltmServerSslProfileC3dCertExtensionCustomOids 2 }

ltmServerSslProfileC3dCertExtensionCustomOidsEntry OBJECT-TYPE
	SYNTAX  LtmServerSslProfileC3dCertExtensionCustomOidsEntry
	MAX-ACCESS not-accessible
	STATUS current
	DESCRIPTION
		"Columns in the ltmServerSslProfileC3dCertExtensionCustomOids Table"
	INDEX {
		ltmServerSslProfileC3dCertExtensionCustomOidsServerssl,
		ltmServerSslProfileC3dCertExtensionCustomOidsIndex
	}
	::= { ltmServerSslProfileC3dCertExtensionCustomOidsTable 1 }

LtmServerSslProfileC3dCertExtensionCustomOidsEntry ::=
	SEQUENCE {
        	ltmServerSslProfileC3dCertExtensionCustomOidsServerssl    LongDisplayString,
        	ltmServerSslProfileC3dCertExtensionCustomOidsIndex        INTEGER,
        	ltmServerSslProfileC3dCertExtensionCustomOidsOid          LongDisplayString
	}

ltmServerSslProfileC3dCertExtensionCustomOidsServerssl OBJECT-TYPE
	SYNTAX LongDisplayString
	MAX-ACCESS read-only
	STATUS current
	DESCRIPTION
		"The name of a server-ssl profile the set is related to."
	::= { ltmServerSslProfileC3dCertExtensionCustomOidsEntry 1 }

ltmServerSslProfileC3dCertExtensionCustomOidsIndex OBJECT-TYPE
	SYNTAX INTEGER(0..2147483647)
	MAX-ACCESS read-only
	STATUS current
	DESCRIPTION
		"The index of the included certificate extension custom OID."
	::= { ltmServerSslProfileC3dCertExtensionCustomOidsEntry 2 }

ltmServerSslProfileC3dCertExtensionCustomOidsOid OBJECT-TYPE
	SYNTAX LongDisplayString
	MAX-ACCESS read-only
	STATUS current
	DESCRIPTION
		"The certificate extension custom OID."
	::= { ltmServerSslProfileC3dCertExtensionCustomOidsEntry 3 }

--==================================================================
-- Source_translation_dynamic
--==================================================================
ltmFwNatDynamicPoolNumber OBJECT-TYPE
	SYNTAX INTEGER
	MAX-ACCESS read-only
	STATUS current
	DESCRIPTION
		"The number of ltmFwNatDynamicPool entries in the table."
	::= { ltmFwNatDynamicPool 1 }

ltmFwNatDynamicPoolTable OBJECT-TYPE
	SYNTAX SEQUENCE OF LtmFwNatDynamicPoolEntry
	MAX-ACCESS not-accessible
	STATUS current
	DESCRIPTION
		"A table containing information for a Dynamic AFM NAT Translation Pool."
	::= { ltmFwNatDynamicPool 2 }

ltmFwNatDynamicPoolEntry OBJECT-TYPE
	SYNTAX  LtmFwNatDynamicPoolEntry
	MAX-ACCESS not-accessible
	STATUS current
	DESCRIPTION
		"Columns in the ltmFwNatDynamicPool Table"
	INDEX {
		ltmFwNatDynamicPoolName
	}
	::= { ltmFwNatDynamicPoolTable 1 }

LtmFwNatDynamicPoolEntry ::=
	SEQUENCE {
        	ltmFwNatDynamicPoolName                                   LongDisplayString,
        	ltmFwNatDynamicPoolDescription                            LongDisplayString,
        	ltmFwNatDynamicPoolAddressCount                           Counter64,
        	ltmFwNatDynamicPoolPortCount                              Counter64,
        	ltmFwNatDynamicPoolAddrFamily                             Gauge,
        	ltmFwNatDynamicPoolType                                   INTEGER,
        	ltmFwNatDynamicPoolPatMode                                INTEGER,
        	ltmFwNatDynamicPoolInboundMode                            INTEGER,
        	ltmFwNatDynamicPoolMappingMode                            Gauge,
        	ltmFwNatDynamicPoolMappingTimeout                         Gauge,
        	ltmFwNatDynamicPoolBlockLifetime                          Gauge,
        	ltmFwNatDynamicPoolBlockIdleTimeout                       Gauge,
        	ltmFwNatDynamicPoolZombieTimeout                          Gauge,
        	ltmFwNatDynamicPoolBlockSize                              Gauge,
        	ltmFwNatDynamicPoolClientBlockLimit                       Gauge,
        	ltmFwNatDynamicPoolRouteAdvertisement                     INTEGER,
        	ltmFwNatDynamicPoolProxyArp                               INTEGER,
        	ltmFwNatDynamicPoolHairpinMode                            INTEGER,
        	ltmFwNatDynamicPoolIcmpEcho                               INTEGER,
        	ltmFwNatDynamicPoolClientConnectionLimit                  Gauge,
        	ltmFwNatDynamicPoolEgressInterfacesEnabled                INTEGER,
        	ltmFwNatDynamicPoolTrafficGroup                           LongDisplayString,
        	ltmFwNatDynamicPoolPcpName                                LongDisplayString,
        	ltmFwNatDynamicPoolPcpSelfipName                          LongDisplayString,
        	ltmFwNatDynamicPoolDsliteTunnel                           LongDisplayString,
        	ltmFwNatDynamicPoolPcpEpoch                               Gauge
	}

ltmFwNatDynamicPoolName OBJECT-TYPE
	SYNTAX LongDisplayString
	MAX-ACCESS read-only
	STATUS current
	DESCRIPTION
		"The name of a Dynamic AFM NAT Translation Pool."
	::= { ltmFwNatDynamicPoolEntry 1 }

ltmFwNatDynamicPoolDescription OBJECT-TYPE
	SYNTAX LongDisplayString
	MAX-ACCESS read-only
	STATUS current
	DESCRIPTION
		"The description of a Dynamic AFM NAT Translation Pool."
	::= { ltmFwNatDynamicPoolEntry 2 }

ltmFwNatDynamicPoolAddressCount OBJECT-TYPE
	SYNTAX Counter64
	MAX-ACCESS read-only
	STATUS current
	DESCRIPTION
		"The address count of a Dynamic AFM NAT Translation Pool."
	::= { ltmFwNatDynamicPoolEntry 3 }

ltmFwNatDynamicPoolPortCount OBJECT-TYPE
	SYNTAX Counter64
	MAX-ACCESS read-only
	STATUS current
	DESCRIPTION
		"The port count of a Dynamic AFM NAT Translation Pool."
	::= { ltmFwNatDynamicPoolEntry 4 }

ltmFwNatDynamicPoolAddrFamily OBJECT-TYPE
	SYNTAX Gauge
	MAX-ACCESS read-only
	STATUS current
	DESCRIPTION
		"The addr family of a Dynamic AFM NAT Translation Pool."
	::= { ltmFwNatDynamicPoolEntry 5 }

ltmFwNatDynamicPoolType OBJECT-TYPE
	SYNTAX INTEGER {
		none(0),
		staticNat(1),
		staticPat(2),
		dynamicNat(3),
		dynamicPat(4)
	}
	MAX-ACCESS read-only
	STATUS current
	DESCRIPTION
		"The type of a Dynamic AFM NAT Translation Pool."
	::= { ltmFwNatDynamicPoolEntry 6 }

ltmFwNatDynamicPoolPatMode OBJECT-TYPE
	SYNTAX INTEGER {
		napt(0),
		pba(1),
		deterministic(2)
	}
	MAX-ACCESS read-only
	STATUS current
	DESCRIPTION
		"The pat mode of a Dynamic AFM NAT Translation Pool."
	::= { ltmFwNatDynamicPoolEntry 7 }

ltmFwNatDynamicPoolInboundMode OBJECT-TYPE
	SYNTAX INTEGER {
		none(0),
		eif(1),
		explicit(2)
	}
	MAX-ACCESS read-only
	STATUS current
	DESCRIPTION
		"The inbound mode of a Dynamic AFM NAT Translation Pool."
	::= { ltmFwNatDynamicPoolEntry 8 }

ltmFwNatDynamicPoolMappingMode OBJECT-TYPE
	SYNTAX Gauge
	MAX-ACCESS read-only
	STATUS current
	DESCRIPTION
		"The mapping mode of a Dynamic AFM NAT Translation Pool."
	::= { ltmFwNatDynamicPoolEntry 9 }

ltmFwNatDynamicPoolMappingTimeout OBJECT-TYPE
	SYNTAX Gauge
	MAX-ACCESS read-only
	STATUS current
	DESCRIPTION
		"The mapping timeout of a Dynamic AFM NAT Translation Pool."
	::= { ltmFwNatDynamicPoolEntry 10 }

ltmFwNatDynamicPoolBlockLifetime OBJECT-TYPE
	SYNTAX Gauge
	MAX-ACCESS read-only
	STATUS current
	DESCRIPTION
		"The block lifetime of a Dynamic AFM NAT Translation Pool."
	::= { ltmFwNatDynamicPoolEntry 11 }

ltmFwNatDynamicPoolBlockIdleTimeout OBJECT-TYPE
	SYNTAX Gauge
	MAX-ACCESS read-only
	STATUS current
	DESCRIPTION
		"The block idle timeout of a Dynamic AFM NAT Translation Pool."
	::= { ltmFwNatDynamicPoolEntry 12 }

ltmFwNatDynamicPoolZombieTimeout OBJECT-TYPE
	SYNTAX Gauge
	MAX-ACCESS read-only
	STATUS current
	DESCRIPTION
		"The zombie timeout of a Dynamic AFM NAT Translation Pool."
	::= { ltmFwNatDynamicPoolEntry 13 }

ltmFwNatDynamicPoolBlockSize OBJECT-TYPE
	SYNTAX Gauge
	MAX-ACCESS read-only
	STATUS current
	DESCRIPTION
		"The block size of a Dynamic AFM NAT Translation Pool."
	::= { ltmFwNatDynamicPoolEntry 14 }

ltmFwNatDynamicPoolClientBlockLimit OBJECT-TYPE
	SYNTAX Gauge
	MAX-ACCESS read-only
	STATUS current
	DESCRIPTION
		"The client block limit of a Dynamic AFM NAT Translation Pool."
	::= { ltmFwNatDynamicPoolEntry 15 }

ltmFwNatDynamicPoolRouteAdvertisement OBJECT-TYPE
	SYNTAX INTEGER {
		false(0),
		true(1)
	}
	MAX-ACCESS read-only
	STATUS current
	DESCRIPTION
		"The route advertisement setting of a Dynamic AFM NAT Translation Pool."
	::= { ltmFwNatDynamicPoolEntry 16 }

ltmFwNatDynamicPoolProxyArp OBJECT-TYPE
	SYNTAX INTEGER {
		false(0),
		true(1)
	}
	MAX-ACCESS read-only
	STATUS current
	DESCRIPTION
		"The proxy arp of a Dynamic AFM NAT Translation Pool."
	::= { ltmFwNatDynamicPoolEntry 17 }

ltmFwNatDynamicPoolHairpinMode OBJECT-TYPE
	SYNTAX INTEGER {
		false(0),
		true(1)
	}
	MAX-ACCESS read-only
	STATUS current
	DESCRIPTION
		"The hairpin mode of a Dynamic AFM NAT Translation Pool."
	::= { ltmFwNatDynamicPoolEntry 18 }

ltmFwNatDynamicPoolIcmpEcho OBJECT-TYPE
	SYNTAX INTEGER {
		false(0),
		true(1)
	}
	MAX-ACCESS read-only
	STATUS current
	DESCRIPTION
		"The icmp echo of a Dynamic AFM NAT Translation Pool."
	::= { ltmFwNatDynamicPoolEntry 19 }

ltmFwNatDynamicPoolClientConnectionLimit OBJECT-TYPE
	SYNTAX Gauge
	MAX-ACCESS read-only
	STATUS current
	DESCRIPTION
		"The client connection limit of a Dynamic AFM NAT Translation Pool."
	::= { ltmFwNatDynamicPoolEntry 20 }

ltmFwNatDynamicPoolEgressInterfacesEnabled OBJECT-TYPE
	SYNTAX INTEGER {
		false(0),
		true(1)
	}
	MAX-ACCESS read-only
	STATUS current
	DESCRIPTION
		"Whether or not the egress interfaces for a Dynamic AFM NAT Translation Pool are enabled."
	::= { ltmFwNatDynamicPoolEntry 21 }

ltmFwNatDynamicPoolTrafficGroup OBJECT-TYPE
	SYNTAX LongDisplayString
	MAX-ACCESS read-only
	STATUS current
	DESCRIPTION
		"The traffic group of a Dynamic AFM NAT Translation Pool."
	::= { ltmFwNatDynamicPoolEntry 22 }

ltmFwNatDynamicPoolPcpName OBJECT-TYPE
	SYNTAX LongDisplayString
	MAX-ACCESS read-only
	STATUS current
	DESCRIPTION
		"The pcp name of a Dynamic AFM NAT Translation Pool."
	::= { ltmFwNatDynamicPoolEntry 23 }

ltmFwNatDynamicPoolPcpSelfipName OBJECT-TYPE
	SYNTAX LongDisplayString
	MAX-ACCESS read-only
	STATUS current
	DESCRIPTION
		"The pcp selfip name of a Dynamic AFM NAT Translation Pool."
	::= { ltmFwNatDynamicPoolEntry 24 }

ltmFwNatDynamicPoolDsliteTunnel OBJECT-TYPE
	SYNTAX LongDisplayString
	MAX-ACCESS read-only
	STATUS current
	DESCRIPTION
		"The dslite tunnel of a Dynamic AFM NAT Translation Pool."
	::= { ltmFwNatDynamicPoolEntry 25 }

ltmFwNatDynamicPoolPcpEpoch OBJECT-TYPE
	SYNTAX Gauge
	MAX-ACCESS read-only
	STATUS current
	DESCRIPTION
		"The pcp epoch of a Dynamic AFM NAT Translation Pool."
	::= { ltmFwNatDynamicPoolEntry 26 }

--==================================================================
-- Source_translation_dynamic_stat
--==================================================================
ltmFwNatDynamicPoolStatResetStats OBJECT-TYPE
	SYNTAX INTEGER
	MAX-ACCESS read-write
	STATUS current
	DESCRIPTION
		"The action to reset resettable statistics data in ltmFwNatDynamicPoolStat.
		 Setting this value to 1 will reset statistics data.
		 Note, some statistics data may not be reset including data that are incremental counters."
	::= { ltmFwNatDynamicPoolStat 1 }

ltmFwNatDynamicPoolStatNumber OBJECT-TYPE
	SYNTAX INTEGER
	MAX-ACCESS read-only
	STATUS current
	DESCRIPTION
		"The number of ltmFwNatDynamicPoolStat entries in the table."
	::= { ltmFwNatDynamicPoolStat 2 }

ltmFwNatDynamicPoolStatTable OBJECT-TYPE
	SYNTAX SEQUENCE OF LtmFwNatDynamicPoolStatEntry
	MAX-ACCESS not-accessible
	STATUS current
	DESCRIPTION
		"A table containing statistic information for a Dynamic AFM NAT Translation Pool."
	::= { ltmFwNatDynamicPoolStat 3 }

ltmFwNatDynamicPoolStatEntry OBJECT-TYPE
	SYNTAX  LtmFwNatDynamicPoolStatEntry
	MAX-ACCESS not-accessible
	STATUS current
	DESCRIPTION
		"Columns in the ltmFwNatDynamicPoolStat Table"
	INDEX {
		ltmFwNatDynamicPoolStatName
	}
	::= { ltmFwNatDynamicPoolStatTable 1 }

LtmFwNatDynamicPoolStatEntry ::=
	SEQUENCE {
        	ltmFwNatDynamicPoolStatName                               LongDisplayString,
        	ltmFwNatDynamicPoolStatLsnTranslationRequests             Counter64,
        	ltmFwNatDynamicPoolStatLsnHairpinConnectionRequests       Counter64,
        	ltmFwNatDynamicPoolStatLsnActiveTranslations              Counter64,
        	ltmFwNatDynamicPoolStatLsnActiveHairpinConnections        Counter64,
        	ltmFwNatDynamicPoolStatLsnTranslationRequestFailures      Counter64,
        	ltmFwNatDynamicPoolStatLsnPersistenceMappingFailures      Counter64,
        	ltmFwNatDynamicPoolStatLsnHairpinConnectionFailures       Counter64,
        	ltmFwNatDynamicPoolStatLsnBackupPoolTranslations          Counter64,
        	ltmFwNatDynamicPoolStatLsnActiveEndPoints                 Counter64,
        	ltmFwNatDynamicPoolStatLsnEndPoints                       Counter64,
        	ltmFwNatDynamicPoolStatLsnEndPointsHighValue              LongDisplayString,
        	ltmFwNatDynamicPoolStatPbaActivePortBlocks                Counter64,
        	ltmFwNatDynamicPoolStatPbaActiveClientsReachedLimit       Counter64,
        	ltmFwNatDynamicPoolStatPbaActiveZombiePortBlocks          Counter64,
        	ltmFwNatDynamicPoolStatPbaPortBlockAllocations            Counter64,
        	ltmFwNatDynamicPoolStatPbaPortBlockAllocationFailures     Counter64,
        	ltmFwNatDynamicPoolStatPbaPortBlockDeallocations          Counter64,
        	ltmFwNatDynamicPoolStatPbaClientsReachedLimit             Counter64,
        	ltmFwNatDynamicPoolStatPbaZombiePortBlocksCreated         Counter64,
        	ltmFwNatDynamicPoolStatPbaZombiePortBlocksDeleted         Counter64,
        	ltmFwNatDynamicPoolStatPbaZombiePortBlockConnsKilled      Counter64,
        	ltmFwNatDynamicPoolStatPcpAnnounceRequests                Counter64,
        	ltmFwNatDynamicPoolStatPcpAnnounceResponsesUcast          Counter64,
        	ltmFwNatDynamicPoolStatPcpAnnounceResponsesMulticast      Counter64,
        	ltmFwNatDynamicPoolStatPcpMapRequests                     Counter64,
        	ltmFwNatDynamicPoolStatPcpMapResponses                    Counter64,
        	ltmFwNatDynamicPoolStatPcpPeerRequests                    Counter64,
        	ltmFwNatDynamicPoolStatPcpPeerResponses                   Counter64,
        	ltmFwNatDynamicPoolStatPcpErrorsInvalidRequest            Counter64,
        	ltmFwNatDynamicPoolStatPcpErrorsUnavailableResource       Counter64,
        	ltmFwNatDynamicPoolStatPcpErrorsNotAuthorized             Counter64,
        	ltmFwNatDynamicPoolStatPcpErrorsOther                     Counter64,
        	ltmFwNatDynamicPoolStatPbaTotalPortBlocks                 Counter64,
        	ltmFwNatDynamicPoolStatPbaPercentFreePortBlocksSnmp       Counter64
	}

ltmFwNatDynamicPoolStatName OBJECT-TYPE
	SYNTAX LongDisplayString
	MAX-ACCESS read-only
	STATUS current
	DESCRIPTION
		"The name of a Dynamic AFM NAT Translation Pool."
	::= { ltmFwNatDynamicPoolStatEntry 1 }

ltmFwNatDynamicPoolStatLsnTranslationRequests OBJECT-TYPE
	SYNTAX Counter64
	MAX-ACCESS read-only
	STATUS current
	DESCRIPTION
		"The number of translation requests."
	::= { ltmFwNatDynamicPoolStatEntry 2 }

ltmFwNatDynamicPoolStatLsnHairpinConnectionRequests OBJECT-TYPE
	SYNTAX Counter64
	MAX-ACCESS read-only
	STATUS current
	DESCRIPTION
		"The number of hairpin connection requests."
	::= { ltmFwNatDynamicPoolStatEntry 3 }

ltmFwNatDynamicPoolStatLsnActiveTranslations OBJECT-TYPE
	SYNTAX Counter64
	MAX-ACCESS read-only
	STATUS current
	DESCRIPTION
		"The number of active translations."
	::= { ltmFwNatDynamicPoolStatEntry 4 }

ltmFwNatDynamicPoolStatLsnActiveHairpinConnections OBJECT-TYPE
	SYNTAX Counter64
	MAX-ACCESS read-only
	STATUS current
	DESCRIPTION
		"The number of active hairpin connections."
	::= { ltmFwNatDynamicPoolStatEntry 5 }

ltmFwNatDynamicPoolStatLsnTranslationRequestFailures OBJECT-TYPE
	SYNTAX Counter64
	MAX-ACCESS read-only
	STATUS current
	DESCRIPTION
		"The number of translation request failures."
	::= { ltmFwNatDynamicPoolStatEntry 6 }

ltmFwNatDynamicPoolStatLsnPersistenceMappingFailures OBJECT-TYPE
	SYNTAX Counter64
	MAX-ACCESS read-only
	STATUS current
	DESCRIPTION
		"The number of persistence mapping failures."
	::= { ltmFwNatDynamicPoolStatEntry 7 }

ltmFwNatDynamicPoolStatLsnHairpinConnectionFailures OBJECT-TYPE
	SYNTAX Counter64
	MAX-ACCESS read-only
	STATUS current
	DESCRIPTION
		"The number of hairpin connection failures."
	::= { ltmFwNatDynamicPoolStatEntry 8 }

ltmFwNatDynamicPoolStatLsnBackupPoolTranslations OBJECT-TYPE
	SYNTAX Counter64
	MAX-ACCESS read-only
	STATUS current
	DESCRIPTION
		"The number of backup pool translations."
	::= { ltmFwNatDynamicPoolStatEntry 9 }

ltmFwNatDynamicPoolStatLsnActiveEndPoints OBJECT-TYPE
	SYNTAX Counter64
	MAX-ACCESS read-only
	STATUS current
	DESCRIPTION
		"The number of active end points."
	::= { ltmFwNatDynamicPoolStatEntry 10 }

ltmFwNatDynamicPoolStatLsnEndPoints OBJECT-TYPE
	SYNTAX Counter64
	MAX-ACCESS read-only
	STATUS current
	DESCRIPTION
		"The number of end points."
	::= { ltmFwNatDynamicPoolStatEntry 11 }

ltmFwNatDynamicPoolStatLsnEndPointsHighValue OBJECT-TYPE
	SYNTAX LongDisplayString
	MAX-ACCESS read-only
	STATUS current
	DESCRIPTION
		"The end points high value."
	::= { ltmFwNatDynamicPoolStatEntry 12 }

ltmFwNatDynamicPoolStatPbaActivePortBlocks OBJECT-TYPE
	SYNTAX Counter64
	MAX-ACCESS read-only
	STATUS current
	DESCRIPTION
		"The number of active port blocks."
	::= { ltmFwNatDynamicPoolStatEntry 13 }

ltmFwNatDynamicPoolStatPbaActiveClientsReachedLimit OBJECT-TYPE
	SYNTAX Counter64
	MAX-ACCESS read-only
	STATUS current
	DESCRIPTION
		"The number of active clients reached limit."
	::= { ltmFwNatDynamicPoolStatEntry 14 }

ltmFwNatDynamicPoolStatPbaActiveZombiePortBlocks OBJECT-TYPE
	SYNTAX Counter64
	MAX-ACCESS read-only
	STATUS current
	DESCRIPTION
		"The number of active zombie port blocks."
	::= { ltmFwNatDynamicPoolStatEntry 15 }

ltmFwNatDynamicPoolStatPbaPortBlockAllocations OBJECT-TYPE
	SYNTAX Counter64
	MAX-ACCESS read-only
	STATUS current
	DESCRIPTION
		"The number of port block allocations."
	::= { ltmFwNatDynamicPoolStatEntry 16 }

ltmFwNatDynamicPoolStatPbaPortBlockAllocationFailures OBJECT-TYPE
	SYNTAX Counter64
	MAX-ACCESS read-only
	STATUS current
	DESCRIPTION
		"The number of port block allocation failures."
	::= { ltmFwNatDynamicPoolStatEntry 17 }

ltmFwNatDynamicPoolStatPbaPortBlockDeallocations OBJECT-TYPE
	SYNTAX Counter64
	MAX-ACCESS read-only
	STATUS current
	DESCRIPTION
		"The number of port block deallocations."
	::= { ltmFwNatDynamicPoolStatEntry 18 }

ltmFwNatDynamicPoolStatPbaClientsReachedLimit OBJECT-TYPE
	SYNTAX Counter64
	MAX-ACCESS read-only
	STATUS current
	DESCRIPTION
		"The number of clients reached limit."
	::= { ltmFwNatDynamicPoolStatEntry 19 }

ltmFwNatDynamicPoolStatPbaZombiePortBlocksCreated OBJECT-TYPE
	SYNTAX Counter64
	MAX-ACCESS read-only
	STATUS current
	DESCRIPTION
		"The number of zombie port blocks created."
	::= { ltmFwNatDynamicPoolStatEntry 20 }

ltmFwNatDynamicPoolStatPbaZombiePortBlocksDeleted OBJECT-TYPE
	SYNTAX Counter64
	MAX-ACCESS read-only
	STATUS current
	DESCRIPTION
		"The number of zombie port blocks deleted."
	::= { ltmFwNatDynamicPoolStatEntry 21 }

ltmFwNatDynamicPoolStatPbaZombiePortBlockConnsKilled OBJECT-TYPE
	SYNTAX Counter64
	MAX-ACCESS read-only
	STATUS current
	DESCRIPTION
		"The number of zombie port block connections killed."
	::= { ltmFwNatDynamicPoolStatEntry 22 }

ltmFwNatDynamicPoolStatPcpAnnounceRequests OBJECT-TYPE
	SYNTAX Counter64
	MAX-ACCESS read-only
	STATUS current
	DESCRIPTION
		"The number of announce requests."
	::= { ltmFwNatDynamicPoolStatEntry 23 }

ltmFwNatDynamicPoolStatPcpAnnounceResponsesUcast OBJECT-TYPE
	SYNTAX Counter64
	MAX-ACCESS read-only
	STATUS current
	DESCRIPTION
		"The number of announce responses ucast."
	::= { ltmFwNatDynamicPoolStatEntry 24 }

ltmFwNatDynamicPoolStatPcpAnnounceResponsesMulticast OBJECT-TYPE
	SYNTAX Counter64
	MAX-ACCESS read-only
	STATUS current
	DESCRIPTION
		"The number of announce responses multicast."
	::= { ltmFwNatDynamicPoolStatEntry 25 }

ltmFwNatDynamicPoolStatPcpMapRequests OBJECT-TYPE
	SYNTAX Counter64
	MAX-ACCESS read-only
	STATUS current
	DESCRIPTION
		"The number of map requests."
	::= { ltmFwNatDynamicPoolStatEntry 26 }

ltmFwNatDynamicPoolStatPcpMapResponses OBJECT-TYPE
	SYNTAX Counter64
	MAX-ACCESS read-only
	STATUS current
	DESCRIPTION
		"The number of map responses."
	::= { ltmFwNatDynamicPoolStatEntry 27 }

ltmFwNatDynamicPoolStatPcpPeerRequests OBJECT-TYPE
	SYNTAX Counter64
	MAX-ACCESS read-only
	STATUS current
	DESCRIPTION
		"The number of peer requests."
	::= { ltmFwNatDynamicPoolStatEntry 28 }

ltmFwNatDynamicPoolStatPcpPeerResponses OBJECT-TYPE
	SYNTAX Counter64
	MAX-ACCESS read-only
	STATUS current
	DESCRIPTION
		"The number of peer responses."
	::= { ltmFwNatDynamicPoolStatEntry 29 }

ltmFwNatDynamicPoolStatPcpErrorsInvalidRequest OBJECT-TYPE
	SYNTAX Counter64
	MAX-ACCESS read-only
	STATUS current
	DESCRIPTION
		"The number of errors: invalid request."
	::= { ltmFwNatDynamicPoolStatEntry 30 }

ltmFwNatDynamicPoolStatPcpErrorsUnavailableResource OBJECT-TYPE
	SYNTAX Counter64
	MAX-ACCESS read-only
	STATUS current
	DESCRIPTION
		"The number of errors: unavailable resource."
	::= { ltmFwNatDynamicPoolStatEntry 31 }

ltmFwNatDynamicPoolStatPcpErrorsNotAuthorized OBJECT-TYPE
	SYNTAX Counter64
	MAX-ACCESS read-only
	STATUS current
	DESCRIPTION
		"The number of errors: not authorized."
	::= { ltmFwNatDynamicPoolStatEntry 32 }

ltmFwNatDynamicPoolStatPcpErrorsOther OBJECT-TYPE
	SYNTAX Counter64
	MAX-ACCESS read-only
	STATUS current
	DESCRIPTION
		"The number of errors: other."
	::= { ltmFwNatDynamicPoolStatEntry 33 }

ltmFwNatDynamicPoolStatPbaTotalPortBlocks OBJECT-TYPE
	SYNTAX Counter64
	MAX-ACCESS read-only
	STATUS current
	DESCRIPTION
		"The total number of port blocks."
	::= { ltmFwNatDynamicPoolStatEntry 34 }

ltmFwNatDynamicPoolStatPbaPercentFreePortBlocksSnmp OBJECT-TYPE
	SYNTAX Counter64
	MAX-ACCESS read-only
	STATUS current
	DESCRIPTION
		"The percentage of free port blocks."
	::= { ltmFwNatDynamicPoolStatEntry 35 }

--==================================================================
-- Source_translation_failure_stat
--==================================================================
ltmFwNatDynamicPoolFailureStatResetStats OBJECT-TYPE
	SYNTAX INTEGER
	MAX-ACCESS read-write
	STATUS current
	DESCRIPTION
		"The action to reset resettable statistics data in ltmFwNatDynamicPoolFailureStat.
		 Setting this value to 1 will reset statistics data.
		 Note, some statistics data may not be reset including data that are incremental counters."
	::= { ltmFwNatDynamicPoolFailureStat 1 }

ltmFwNatDynamicPoolFailureStatNumber OBJECT-TYPE
	SYNTAX INTEGER
	MAX-ACCESS read-only
	STATUS current
	DESCRIPTION
		"The number of ltmFwNatDynamicPoolFailureStat entries in the table."
	::= { ltmFwNatDynamicPoolFailureStat 2 }

ltmFwNatDynamicPoolFailureStatTable OBJECT-TYPE
	SYNTAX SEQUENCE OF LtmFwNatDynamicPoolFailureStatEntry
	MAX-ACCESS not-accessible
	STATUS current
	DESCRIPTION
		"A table containing statistic information for Dynamic AFM NAT Translation Pool failures."
	::= { ltmFwNatDynamicPoolFailureStat 3 }

ltmFwNatDynamicPoolFailureStatEntry OBJECT-TYPE
	SYNTAX  LtmFwNatDynamicPoolFailureStatEntry
	MAX-ACCESS not-accessible
	STATUS current
	DESCRIPTION
		"Columns in the ltmFwNatDynamicPoolFailureStat Table"
	INDEX {
		ltmFwNatDynamicPoolFailureStatName,
		ltmFwNatDynamicPoolFailureStatFailureCause
	}
	::= { ltmFwNatDynamicPoolFailureStatTable 1 }

LtmFwNatDynamicPoolFailureStatEntry ::=
	SEQUENCE {
        	ltmFwNatDynamicPoolFailureStatName                        LongDisplayString,
        	ltmFwNatDynamicPoolFailureStatFailureCause                LongDisplayString,
        	ltmFwNatDynamicPoolFailureStatFailureCount                Counter64
	}

ltmFwNatDynamicPoolFailureStatName OBJECT-TYPE
	SYNTAX LongDisplayString
	MAX-ACCESS read-only
	STATUS current
	DESCRIPTION
		"The name of a Dynamic AFM NAT Translation Pool."
	::= { ltmFwNatDynamicPoolFailureStatEntry 1 }

ltmFwNatDynamicPoolFailureStatFailureCause OBJECT-TYPE
	SYNTAX LongDisplayString
	MAX-ACCESS read-only
	STATUS current
	DESCRIPTION
		"The name of a Dynamic AFM NAT Translation Pool failure cause."
	::= { ltmFwNatDynamicPoolFailureStatEntry 2 }

ltmFwNatDynamicPoolFailureStatFailureCount OBJECT-TYPE
	SYNTAX Counter64
	MAX-ACCESS read-only
	STATUS current
	DESCRIPTION
		"The value of a Dynamic AFM NAT Translation Pool failure cause."
	::= { ltmFwNatDynamicPoolFailureStatEntry 3 }

--==================================================================
-- Destination_translation_static
--==================================================================
ltmFwNatStaticDestinationTranslationPoolNumber OBJECT-TYPE
	SYNTAX INTEGER
	MAX-ACCESS read-only
	STATUS current
	DESCRIPTION
		"The number of ltmFwNatStaticDestinationTranslationPool entries in the table."
	::= { ltmFwNatStaticDestinationTranslationPool 1 }

ltmFwNatStaticDestinationTranslationPoolTable OBJECT-TYPE
	SYNTAX SEQUENCE OF LtmFwNatStaticDestinationTranslationPoolEntry
	MAX-ACCESS not-accessible
	STATUS current
	DESCRIPTION
		"A table containing information for a Static AFM NAT Destination Translation Pool."
	::= { ltmFwNatStaticDestinationTranslationPool 2 }

ltmFwNatStaticDestinationTranslationPoolEntry OBJECT-TYPE
	SYNTAX  LtmFwNatStaticDestinationTranslationPoolEntry
	MAX-ACCESS not-accessible
	STATUS current
	DESCRIPTION
		"Columns in the ltmFwNatStaticDestinationTranslationPool Table"
	INDEX {
		ltmFwNatStaticDestinationTranslationPoolName
	}
	::= { ltmFwNatStaticDestinationTranslationPoolTable 1 }

LtmFwNatStaticDestinationTranslationPoolEntry ::=
	SEQUENCE {
        	ltmFwNatStaticDestinationTranslationPoolName              LongDisplayString,
        	ltmFwNatStaticDestinationTranslationPoolDescription       LongDisplayString,
        	ltmFwNatStaticDestinationTranslationPoolType              INTEGER,
        	ltmFwNatStaticDestinationTranslationPoolPortCount         Counter64
	}

ltmFwNatStaticDestinationTranslationPoolName OBJECT-TYPE
	SYNTAX LongDisplayString
	MAX-ACCESS read-only
	STATUS current
	DESCRIPTION
		"The name of a Static AFM NAT Destination Translation Pool."
	::= { ltmFwNatStaticDestinationTranslationPoolEntry 1 }

ltmFwNatStaticDestinationTranslationPoolDescription OBJECT-TYPE
	SYNTAX LongDisplayString
	MAX-ACCESS read-only
	STATUS current
	DESCRIPTION
		"The description of a Static AFM NAT Destination Translation Pool."
	::= { ltmFwNatStaticDestinationTranslationPoolEntry 2 }

ltmFwNatStaticDestinationTranslationPoolType OBJECT-TYPE
	SYNTAX INTEGER {
		none(0),
		staticNat(1),
		staticPat(2),
		dynamicNat(3),
		dynamicPat(4)
	}
	MAX-ACCESS read-only
	STATUS current
	DESCRIPTION
		"The type of a Static AFM NAT Destination Translation Pool."
	::= { ltmFwNatStaticDestinationTranslationPoolEntry 3 }

ltmFwNatStaticDestinationTranslationPoolPortCount OBJECT-TYPE
	SYNTAX Counter64
	MAX-ACCESS read-only
	STATUS current
	DESCRIPTION
		"The port count of a Static AFM NAT Destination Translation Pool."
	::= { ltmFwNatStaticDestinationTranslationPoolEntry 4 }

--==================================================================
-- Destination_translation_static_stat
--==================================================================
ltmFwNatStaticDestinationTranslationPoolStatResetStats OBJECT-TYPE
	SYNTAX INTEGER
	MAX-ACCESS read-write
	STATUS current
	DESCRIPTION
		"The action to reset resettable statistics data in ltmFwNatStaticDestinationTranslationPoolStat.
		 Setting this value to 1 will reset statistics data.
		 Note, some statistics data may not be reset including data that are incremental counters."
	::= { ltmFwNatStaticDestinationTranslationPoolStat 1 }

ltmFwNatStaticDestinationTranslationPoolStatNumber OBJECT-TYPE
	SYNTAX INTEGER
	MAX-ACCESS read-only
	STATUS current
	DESCRIPTION
		"The number of ltmFwNatStaticDestinationTranslationPoolStat entries in the table."
	::= { ltmFwNatStaticDestinationTranslationPoolStat 2 }

ltmFwNatStaticDestinationTranslationPoolStatTable OBJECT-TYPE
	SYNTAX SEQUENCE OF LtmFwNatStaticDestinationTranslationPoolStatEntry
	MAX-ACCESS not-accessible
	STATUS current
	DESCRIPTION
		"A table containing statistic information for a Static AFM NAT Destination Translation Pool."
	::= { ltmFwNatStaticDestinationTranslationPoolStat 3 }

ltmFwNatStaticDestinationTranslationPoolStatEntry OBJECT-TYPE
	SYNTAX  LtmFwNatStaticDestinationTranslationPoolStatEntry
	MAX-ACCESS not-accessible
	STATUS current
	DESCRIPTION
		"Columns in the ltmFwNatStaticDestinationTranslationPoolStat Table"
	INDEX {
		ltmFwNatStaticDestinationTranslationPoolStatName
	}
	::= { ltmFwNatStaticDestinationTranslationPoolStatTable 1 }

LtmFwNatStaticDestinationTranslationPoolStatEntry ::=
	SEQUENCE {
        	ltmFwNatStaticDestinationTranslationPoolStatName          LongDisplayString,
        	ltmFwNatStaticDestinationTranslationPoolStatTransReqs     Counter64,
        	ltmFwNatStaticDestinationTranslationPoolStatTransReqFails Counter64,
        	ltmFwNatStaticDestinationTranslationPoolStatBidirReqs     Counter64,
        	ltmFwNatStaticDestinationTranslationPoolStatBidirReqFails Counter64,
        	ltmFwNatStaticDestinationTranslationPoolStatErrAddrTrans  Counter64,
        	ltmFwNatStaticDestinationTranslationPoolStatErrPortTrans  Counter64,
        	ltmFwNatStaticDestinationTranslationPoolStatErrFlowCollis Counter64,
        	ltmFwNatStaticDestinationTranslationPoolStatErrCfgMismtch Counter64,
        	ltmFwNatStaticDestinationTranslationPoolStatErrMemory     Counter64,
        	ltmFwNatStaticDestinationTranslationPoolStatSubscrIdLkps  Counter64,
        	ltmFwNatStaticDestinationTranslationPoolStatSubscrIdNotFd Counter64,
        	ltmFwNatStaticDestinationTranslationPoolStatSubscrIdErrs  Counter64
	}

ltmFwNatStaticDestinationTranslationPoolStatName OBJECT-TYPE
	SYNTAX LongDisplayString
	MAX-ACCESS read-only
	STATUS current
	DESCRIPTION
		"The name of a Static AFM NAT Destination Translation Pool."
	::= { ltmFwNatStaticDestinationTranslationPoolStatEntry 1 }

ltmFwNatStaticDestinationTranslationPoolStatTransReqs OBJECT-TYPE
	SYNTAX Counter64
	MAX-ACCESS read-only
	STATUS current
	DESCRIPTION
		"The number of translation requests."
	::= { ltmFwNatStaticDestinationTranslationPoolStatEntry 2 }

ltmFwNatStaticDestinationTranslationPoolStatTransReqFails OBJECT-TYPE
	SYNTAX Counter64
	MAX-ACCESS read-only
	STATUS current
	DESCRIPTION
		"The number of translation request failures."
	::= { ltmFwNatStaticDestinationTranslationPoolStatEntry 3 }

ltmFwNatStaticDestinationTranslationPoolStatBidirReqs OBJECT-TYPE
	SYNTAX Counter64
	MAX-ACCESS read-only
	STATUS current
	DESCRIPTION
		"The number of bidirectional requests."
	::= { ltmFwNatStaticDestinationTranslationPoolStatEntry 4 }

ltmFwNatStaticDestinationTranslationPoolStatBidirReqFails OBJECT-TYPE
	SYNTAX Counter64
	MAX-ACCESS read-only
	STATUS current
	DESCRIPTION
		"The number of bidirectional request failures."
	::= { ltmFwNatStaticDestinationTranslationPoolStatEntry 5 }

ltmFwNatStaticDestinationTranslationPoolStatErrAddrTrans OBJECT-TYPE
	SYNTAX Counter64
	MAX-ACCESS read-only
	STATUS current
	DESCRIPTION
		"The number of err address translation events."
	::= { ltmFwNatStaticDestinationTranslationPoolStatEntry 6 }

ltmFwNatStaticDestinationTranslationPoolStatErrPortTrans OBJECT-TYPE
	SYNTAX Counter64
	MAX-ACCESS read-only
	STATUS current
	DESCRIPTION
		"The number of err port translation events."
	::= { ltmFwNatStaticDestinationTranslationPoolStatEntry 7 }

ltmFwNatStaticDestinationTranslationPoolStatErrFlowCollis OBJECT-TYPE
	SYNTAX Counter64
	MAX-ACCESS read-only
	STATUS current
	DESCRIPTION
		"The number of err flow collision events."
	::= { ltmFwNatStaticDestinationTranslationPoolStatEntry 8 }

ltmFwNatStaticDestinationTranslationPoolStatErrCfgMismtch OBJECT-TYPE
	SYNTAX Counter64
	MAX-ACCESS read-only
	STATUS current
	DESCRIPTION
		"The number of err config mismatch events."
	::= { ltmFwNatStaticDestinationTranslationPoolStatEntry 9 }

ltmFwNatStaticDestinationTranslationPoolStatErrMemory OBJECT-TYPE
	SYNTAX Counter64
	MAX-ACCESS read-only
	STATUS current
	DESCRIPTION
		"The number of err memory events."
	::= { ltmFwNatStaticDestinationTranslationPoolStatEntry 10 }

ltmFwNatStaticDestinationTranslationPoolStatSubscrIdLkps OBJECT-TYPE
	SYNTAX Counter64
	MAX-ACCESS read-only
	STATUS current
	DESCRIPTION
		"The number of subscriber id lookups."
	::= { ltmFwNatStaticDestinationTranslationPoolStatEntry 11 }

ltmFwNatStaticDestinationTranslationPoolStatSubscrIdNotFd OBJECT-TYPE
	SYNTAX Counter64
	MAX-ACCESS read-only
	STATUS current
	DESCRIPTION
		"The number of subscriber id not found events."
	::= { ltmFwNatStaticDestinationTranslationPoolStatEntry 12 }

ltmFwNatStaticDestinationTranslationPoolStatSubscrIdErrs OBJECT-TYPE
	SYNTAX Counter64
	MAX-ACCESS read-only
	STATUS current
	DESCRIPTION
		"The number of subscriber id errors."
	::= { ltmFwNatStaticDestinationTranslationPoolStatEntry 13 }

--==================================================================
-- Source_translation_static
--==================================================================
ltmFwNatStaticSourceTranslationPoolNumber OBJECT-TYPE
	SYNTAX INTEGER
	MAX-ACCESS read-only
	STATUS current
	DESCRIPTION
		"The number of ltmFwNatStaticSourceTranslationPool entries in the table."
	::= { ltmFwNatStaticSourceTranslationPool 1 }

ltmFwNatStaticSourceTranslationPoolTable OBJECT-TYPE
	SYNTAX SEQUENCE OF LtmFwNatStaticSourceTranslationPoolEntry
	MAX-ACCESS not-accessible
	STATUS current
	DESCRIPTION
		"A table containing information for a Static AFM NAT Source Translation Pool."
	::= { ltmFwNatStaticSourceTranslationPool 2 }

ltmFwNatStaticSourceTranslationPoolEntry OBJECT-TYPE
	SYNTAX  LtmFwNatStaticSourceTranslationPoolEntry
	MAX-ACCESS not-accessible
	STATUS current
	DESCRIPTION
		"Columns in the ltmFwNatStaticSourceTranslationPool Table"
	INDEX {
		ltmFwNatStaticSourceTranslationPoolName
	}
	::= { ltmFwNatStaticSourceTranslationPoolTable 1 }

LtmFwNatStaticSourceTranslationPoolEntry ::=
	SEQUENCE {
        	ltmFwNatStaticSourceTranslationPoolName                   LongDisplayString,
        	ltmFwNatStaticSourceTranslationPoolDescription            LongDisplayString,
        	ltmFwNatStaticSourceTranslationPoolPortCount              Counter64,
        	ltmFwNatStaticSourceTranslationPoolType                   INTEGER,
        	ltmFwNatStaticSourceTranslationPoolRouteAdvertisement     INTEGER,
        	ltmFwNatStaticSourceTranslationPoolProxyArp               INTEGER,
        	ltmFwNatStaticSourceTranslationPoolIcmpEcho               INTEGER,
        	ltmFwNatStaticSourceTranslationPoolEgressIfcsEnabled      INTEGER
	}

ltmFwNatStaticSourceTranslationPoolName OBJECT-TYPE
	SYNTAX LongDisplayString
	MAX-ACCESS read-only
	STATUS current
	DESCRIPTION
		"The name of a Static AFM NAT Source Translation Pool."
	::= { ltmFwNatStaticSourceTranslationPoolEntry 1 }

ltmFwNatStaticSourceTranslationPoolDescription OBJECT-TYPE
	SYNTAX LongDisplayString
	MAX-ACCESS read-only
	STATUS current
	DESCRIPTION
		"The description of a Static AFM NAT Source Translation Pool."
	::= { ltmFwNatStaticSourceTranslationPoolEntry 2 }

ltmFwNatStaticSourceTranslationPoolPortCount OBJECT-TYPE
	SYNTAX Counter64
	MAX-ACCESS read-only
	STATUS current
	DESCRIPTION
		"The port count of a Static AFM NAT Source Translation Pool."
	::= { ltmFwNatStaticSourceTranslationPoolEntry 3 }

ltmFwNatStaticSourceTranslationPoolType OBJECT-TYPE
	SYNTAX INTEGER {
		none(0),
		staticNat(1),
		staticPat(2),
		dynamicNat(3),
		dynamicPat(4)
	}
	MAX-ACCESS read-only
	STATUS current
	DESCRIPTION
		"The type of a Static AFM NAT Source Translation Pool."
	::= { ltmFwNatStaticSourceTranslationPoolEntry 4 }

ltmFwNatStaticSourceTranslationPoolRouteAdvertisement OBJECT-TYPE
	SYNTAX INTEGER {
		false(0),
		true(1)
	}
	MAX-ACCESS read-only
	STATUS current
	DESCRIPTION
		"The route advertisement setting of a Static AFM NAT Source Translation Pool."
	::= { ltmFwNatStaticSourceTranslationPoolEntry 5 }

ltmFwNatStaticSourceTranslationPoolProxyArp OBJECT-TYPE
	SYNTAX INTEGER {
		false(0),
		true(1)
	}
	MAX-ACCESS read-only
	STATUS current
	DESCRIPTION
		"The proxy arp of a Static AFM NAT Source Translation Pool."
	::= { ltmFwNatStaticSourceTranslationPoolEntry 6 }

ltmFwNatStaticSourceTranslationPoolIcmpEcho OBJECT-TYPE
	SYNTAX INTEGER {
		false(0),
		true(1)
	}
	MAX-ACCESS read-only
	STATUS current
	DESCRIPTION
		"The icmp echo of a Static AFM NAT Source Translation Pool."
	::= { ltmFwNatStaticSourceTranslationPoolEntry 7 }

ltmFwNatStaticSourceTranslationPoolEgressIfcsEnabled OBJECT-TYPE
	SYNTAX INTEGER {
		false(0),
		true(1)
	}
	MAX-ACCESS read-only
	STATUS current
	DESCRIPTION
		"Whether or not the egress interfaces for a Static AFM NAT Source Translation Pool are enabled."
	::= { ltmFwNatStaticSourceTranslationPoolEntry 8 }

--==================================================================
-- Source_translation_static_stat
--==================================================================
ltmFwNatStaticSourceTranslationPoolStatResetStats OBJECT-TYPE
	SYNTAX INTEGER
	MAX-ACCESS read-write
	STATUS current
	DESCRIPTION
		"The action to reset resettable statistics data in ltmFwNatStaticSourceTranslationPoolStat.
		 Setting this value to 1 will reset statistics data.
		 Note, some statistics data may not be reset including data that are incremental counters."
	::= { ltmFwNatStaticSourceTranslationPoolStat 1 }

ltmFwNatStaticSourceTranslationPoolStatNumber OBJECT-TYPE
	SYNTAX INTEGER
	MAX-ACCESS read-only
	STATUS current
	DESCRIPTION
		"The number of ltmFwNatStaticSourceTranslationPoolStat entries in the table."
	::= { ltmFwNatStaticSourceTranslationPoolStat 2 }

ltmFwNatStaticSourceTranslationPoolStatTable OBJECT-TYPE
	SYNTAX SEQUENCE OF LtmFwNatStaticSourceTranslationPoolStatEntry
	MAX-ACCESS not-accessible
	STATUS current
	DESCRIPTION
		"A table containing statistic information for a Static AFM NAT Source Translation Pool."
	::= { ltmFwNatStaticSourceTranslationPoolStat 3 }

ltmFwNatStaticSourceTranslationPoolStatEntry OBJECT-TYPE
	SYNTAX  LtmFwNatStaticSourceTranslationPoolStatEntry
	MAX-ACCESS not-accessible
	STATUS current
	DESCRIPTION
		"Columns in the ltmFwNatStaticSourceTranslationPoolStat Table"
	INDEX {
		ltmFwNatStaticSourceTranslationPoolStatName
	}
	::= { ltmFwNatStaticSourceTranslationPoolStatTable 1 }

LtmFwNatStaticSourceTranslationPoolStatEntry ::=
	SEQUENCE {
        	ltmFwNatStaticSourceTranslationPoolStatName               LongDisplayString,
        	ltmFwNatStaticSourceTranslationPoolStatTransReqs          Counter64,
        	ltmFwNatStaticSourceTranslationPoolStatTransReqFails      Counter64,
        	ltmFwNatStaticSourceTranslationPoolStatBidirReqs          Counter64,
        	ltmFwNatStaticSourceTranslationPoolStatBidirReqFails      Counter64,
        	ltmFwNatStaticSourceTranslationPoolStatErrAddrTrans       Counter64,
        	ltmFwNatStaticSourceTranslationPoolStatErrPortTrans       Counter64,
        	ltmFwNatStaticSourceTranslationPoolStatErrFlowCollis      Counter64,
        	ltmFwNatStaticSourceTranslationPoolStatErrCfgMismtch      Counter64,
        	ltmFwNatStaticSourceTranslationPoolStatErrMemory          Counter64,
        	ltmFwNatStaticSourceTranslationPoolStatSubscrIdLkps       Counter64,
        	ltmFwNatStaticSourceTranslationPoolStatSubscrIdNotFd      Counter64,
        	ltmFwNatStaticSourceTranslationPoolStatSubscrIdErrs       Counter64
	}

ltmFwNatStaticSourceTranslationPoolStatName OBJECT-TYPE
	SYNTAX LongDisplayString
	MAX-ACCESS read-only
	STATUS current
	DESCRIPTION
		"The name of a Static AFM NAT Source Translation Pool."
	::= { ltmFwNatStaticSourceTranslationPoolStatEntry 1 }

ltmFwNatStaticSourceTranslationPoolStatTransReqs OBJECT-TYPE
	SYNTAX Counter64
	MAX-ACCESS read-only
	STATUS current
	DESCRIPTION
		"The number of translation requests."
	::= { ltmFwNatStaticSourceTranslationPoolStatEntry 2 }

ltmFwNatStaticSourceTranslationPoolStatTransReqFails OBJECT-TYPE
	SYNTAX Counter64
	MAX-ACCESS read-only
	STATUS current
	DESCRIPTION
		"The number of translation request failures."
	::= { ltmFwNatStaticSourceTranslationPoolStatEntry 3 }

ltmFwNatStaticSourceTranslationPoolStatBidirReqs OBJECT-TYPE
	SYNTAX Counter64
	MAX-ACCESS read-only
	STATUS current
	DESCRIPTION
		"The number of bidirectional requests."
	::= { ltmFwNatStaticSourceTranslationPoolStatEntry 4 }

ltmFwNatStaticSourceTranslationPoolStatBidirReqFails OBJECT-TYPE
	SYNTAX Counter64
	MAX-ACCESS read-only
	STATUS current
	DESCRIPTION
		"The number of bidirectional request failures."
	::= { ltmFwNatStaticSourceTranslationPoolStatEntry 5 }

ltmFwNatStaticSourceTranslationPoolStatErrAddrTrans OBJECT-TYPE
	SYNTAX Counter64
	MAX-ACCESS read-only
	STATUS current
	DESCRIPTION
		"The number of err address translation events."
	::= { ltmFwNatStaticSourceTranslationPoolStatEntry 6 }

ltmFwNatStaticSourceTranslationPoolStatErrPortTrans OBJECT-TYPE
	SYNTAX Counter64
	MAX-ACCESS read-only
	STATUS current
	DESCRIPTION
		"The number of err port translation events."
	::= { ltmFwNatStaticSourceTranslationPoolStatEntry 7 }

ltmFwNatStaticSourceTranslationPoolStatErrFlowCollis OBJECT-TYPE
	SYNTAX Counter64
	MAX-ACCESS read-only
	STATUS current
	DESCRIPTION
		"The number of err flow collision events."
	::= { ltmFwNatStaticSourceTranslationPoolStatEntry 8 }

ltmFwNatStaticSourceTranslationPoolStatErrCfgMismtch OBJECT-TYPE
	SYNTAX Counter64
	MAX-ACCESS read-only
	STATUS current
	DESCRIPTION
		"The number of err config mismatch events."
	::= { ltmFwNatStaticSourceTranslationPoolStatEntry 9 }

ltmFwNatStaticSourceTranslationPoolStatErrMemory OBJECT-TYPE
	SYNTAX Counter64
	MAX-ACCESS read-only
	STATUS current
	DESCRIPTION
		"The number of err memory events."
	::= { ltmFwNatStaticSourceTranslationPoolStatEntry 10 }

ltmFwNatStaticSourceTranslationPoolStatSubscrIdLkps OBJECT-TYPE
	SYNTAX Counter64
	MAX-ACCESS read-only
	STATUS current
	DESCRIPTION
		"The number of subscriber id lookups."
	::= { ltmFwNatStaticSourceTranslationPoolStatEntry 11 }

ltmFwNatStaticSourceTranslationPoolStatSubscrIdNotFd OBJECT-TYPE
	SYNTAX Counter64
	MAX-ACCESS read-only
	STATUS current
	DESCRIPTION
		"The number of subscriber id not found events."
	::= { ltmFwNatStaticSourceTranslationPoolStatEntry 12 }

ltmFwNatStaticSourceTranslationPoolStatSubscrIdErrs OBJECT-TYPE
	SYNTAX Counter64
	MAX-ACCESS read-only
	STATUS current
	DESCRIPTION
		"The number of subscriber id errors."
	::= { ltmFwNatStaticSourceTranslationPoolStatEntry 13 }

--================================================================
 -- Compliance and Group
--================================================================

bigipLocalTMCompliance	MODULE-COMPLIANCE
	STATUS current
	DESCRIPTION
		"This specifies the objects that are required to claim
                 compliance to F5 Traffic Management System."
	MODULE
	  MANDATORY-GROUPS { bigipLocalTMGroups }
	::= { bigipCompliances 2 }

bigipLocalTMGroups  OBJECT IDENTIFIER ::= {  bigipGroups 2 }

ltmAttrGroup OBJECT-GROUP
	 OBJECTS {
		ltmAttrLbmodeFastestMaxIdleTime,
		ltmAttrMirrorState,
		ltmAttrPersistDestAddrLimitMode,
		ltmAttrPersistDestAddrMaxCount,
		ltmAttrSnatAnyIpProtocol,
		ltmAttrMirrorPeerIpAddr
	}
	STATUS	 current
	DESCRIPTION
		"A collection of objects of ltmGlobalAttr MIB."
	::= { bigipLocalTMGroups 1 }

ltmRateFilterGroup OBJECT-GROUP
	 OBJECTS {
		ltmRateFilterNumber,
		ltmRateFilterCname,
		ltmRateFilterRate,
		ltmRateFilterCeil,
		ltmRateFilterBurst,
		ltmRateFilterPname,
		ltmRateFilterQtype,
		ltmRateFilterDirection
	}
	STATUS	 current
	DESCRIPTION
		"A collection of objects of ltmRateFilter MIB."
	::= { bigipLocalTMGroups 2 }

ltmRateFilterStatGroup OBJECT-GROUP
	 OBJECTS {
		ltmRateFilterStatResetStats,
		ltmRateFilterStatNumber,
		ltmRateFilterStatCname,
		ltmRateFilterStatRateBytes,
		ltmRateFilterStatBurstBytes,
		ltmRateFilterStatDroppedBytes,
		ltmRateFilterStatBytesQueued,
		ltmRateFilterStatBytesPerSec,
		ltmRateFilterStatDropTailPkts,
		ltmRateFilterStatDropTailBytes,
		ltmRateFilterStatDropRandPkts,
		ltmRateFilterStatDropRandBytes,
		ltmRateFilterStatDropTotPkts,
		ltmRateFilterStatDropTotBytes
	}
	STATUS	 current
	DESCRIPTION
		"A collection of objects of ltmRateFilterStat MIB."
	::= { bigipLocalTMGroups 3 }

ltmMirrorPortGroup OBJECT-GROUP
	 OBJECTS {
		ltmMirrorPortNumber,
		ltmMirrorPortName
	}
	STATUS	 current
	DESCRIPTION
		"A collection of objects of ltmMirrorPort MIB."
	::= { bigipLocalTMGroups 4 }

ltmMirrorPortMemberGroup OBJECT-GROUP
	 OBJECTS {
		ltmMirrorPortMemberNumber,
		ltmMirrorPortMemberToName,
		ltmMirrorPortMemberName,
		ltmMirrorPortMemberConduitName
	}
	STATUS	 current
	DESCRIPTION
		"A collection of objects of ltmMirrorPortMember MIB."
	::= { bigipLocalTMGroups 5 }

ltmNatGroup OBJECT-GROUP
	 OBJECTS {
		ltmNatNumber,
		ltmNatTransAddrType,
		ltmNatTransAddr,
		ltmNatOrigAddrType,
		ltmNatOrigAddr,
		ltmNatEnabled,
		ltmNatArpEnabled,
		ltmNatUnitId,
		ltmNatListedEnabledVlans,
		ltmNatName
	}
	STATUS	 current
	DESCRIPTION
		"A collection of objects of ltmNat MIB."
	::= { bigipLocalTMGroups 6 }

ltmNatStatGroup OBJECT-GROUP
	 OBJECTS {
		ltmNatStatResetStats,
		ltmNatStatNumber,
		ltmNatStatTransAddrType,
		ltmNatStatTransAddr,
		ltmNatStatServerPktsIn,
		ltmNatStatServerBytesIn,
		ltmNatStatServerPktsOut,
		ltmNatStatServerBytesOut,
		ltmNatStatServerMaxConns,
		ltmNatStatServerTotConns,
		ltmNatStatServerCurConns,
		ltmNatStatName
	}
	STATUS	 current
	DESCRIPTION
		"A collection of objects of ltmNatStat MIB."
	::= { bigipLocalTMGroups 7 }

ltmNatVlanGroup OBJECT-GROUP
	 OBJECTS {
		ltmNatVlanNumber,
		ltmNatVlanTransAddrType,
		ltmNatVlanTransAddr,
		ltmNatVlanVlanName,
		ltmNatVlanNatName
	}
	STATUS	 current
	DESCRIPTION
		"A collection of objects of ltmNatVlan MIB."
	::= { bigipLocalTMGroups 8 }

ltmNodeAddrGroup OBJECT-GROUP
	 OBJECTS {
		ltmNodeAddrNumber,
		ltmNodeAddrAddrType,
		ltmNodeAddrAddr,
		ltmNodeAddrConnLimit,
		ltmNodeAddrRatio,
		ltmNodeAddrDynamicRatio,
		ltmNodeAddrMonitorState,
		ltmNodeAddrMonitorStatus,
		ltmNodeAddrMonitorRule,
		ltmNodeAddrNewSessionEnable,
		ltmNodeAddrSessionStatus,
		ltmNodeAddrPoolMemberRefCount,
		ltmNodeAddrScreenName,
		ltmNodeAddrAvailabilityState,
		ltmNodeAddrEnabledState,
		ltmNodeAddrDisabledParentType,
		ltmNodeAddrStatusReason,
		ltmNodeAddrName
	}
	STATUS	 current
	DESCRIPTION
		"A collection of objects of ltmNodeAddr MIB."
	::= { bigipLocalTMGroups 9 }

ltmNodeAddrStatGroup OBJECT-GROUP
	 OBJECTS {
		ltmNodeAddrStatResetStats,
		ltmNodeAddrStatNumber,
		ltmNodeAddrStatAddrType,
		ltmNodeAddrStatAddr,
		ltmNodeAddrStatServerPktsIn,
		ltmNodeAddrStatServerBytesIn,
		ltmNodeAddrStatServerPktsOut,
		ltmNodeAddrStatServerBytesOut,
		ltmNodeAddrStatServerMaxConns,
		ltmNodeAddrStatServerTotConns,
		ltmNodeAddrStatServerCurConns,
		ltmNodeAddrStatPvaPktsIn,
		ltmNodeAddrStatPvaBytesIn,
		ltmNodeAddrStatPvaPktsOut,
		ltmNodeAddrStatPvaBytesOut,
		ltmNodeAddrStatPvaMaxConns,
		ltmNodeAddrStatPvaTotConns,
		ltmNodeAddrStatPvaCurConns,
		ltmNodeAddrStatTotRequests,
		ltmNodeAddrStatTotPvaAssistConn,
		ltmNodeAddrStatCurrPvaAssistConn,
		ltmNodeAddrStatNodeName,
		ltmNodeAddrStatCurSessions,
		ltmNodeAddrStatCurrentConnsPerSec,
		ltmNodeAddrStatDurationRateExceeded
	}
	STATUS	 current
	DESCRIPTION
		"A collection of objects of ltmNodeAddrStat MIB."
	::= { bigipLocalTMGroups 10 }

ltmPoolGroup OBJECT-GROUP
	 OBJECTS {
		ltmPoolNumber,
		ltmPoolName,
		ltmPoolLbMode,
		ltmPoolActionOnServiceDown,
		ltmPoolMinUpMembers,
		ltmPoolMinUpMembersEnable,
		ltmPoolMinUpMemberAction,
		ltmPoolMinActiveMembers,
		ltmPoolActiveMemberCnt,
		ltmPoolDisallowSnat,
		ltmPoolDisallowNat,
		ltmPoolSimpleTimeout,
		ltmPoolIpTosToClient,
		ltmPoolIpTosToServer,
		ltmPoolLinkQosToClient,
		ltmPoolLinkQosToServer,
		ltmPoolDynamicRatioSum,
		ltmPoolMonitorRule,
		ltmPoolAvailabilityState,
		ltmPoolEnabledState,
		ltmPoolDisabledParentType,
		ltmPoolStatusReason,
		ltmPoolSlowRampTime,
		ltmPoolMemberCnt,
		ltmPoolQueueOnConnectionLimit,
		ltmPoolQueueDepthLimit,
		ltmPoolQueueTimeLimit,
		ltmPoolDescription
	}
	STATUS	 current
	DESCRIPTION
		"A collection of objects of ltmPool MIB."
	::= { bigipLocalTMGroups 11 }

ltmPoolStatGroup OBJECT-GROUP
	 OBJECTS {
		ltmPoolStatResetStats,
		ltmPoolStatNumber,
		ltmPoolStatName,
		ltmPoolStatServerPktsIn,
		ltmPoolStatServerBytesIn,
		ltmPoolStatServerPktsOut,
		ltmPoolStatServerBytesOut,
		ltmPoolStatServerMaxConns,
		ltmPoolStatServerTotConns,
		ltmPoolStatServerCurConns,
		ltmPoolStatPvaPktsIn,
		ltmPoolStatPvaBytesIn,
		ltmPoolStatPvaPktsOut,
		ltmPoolStatPvaBytesOut,
		ltmPoolStatPvaMaxConns,
		ltmPoolStatPvaTotConns,
		ltmPoolStatPvaCurConns,
		ltmPoolStatTotPvaAssistConn,
		ltmPoolStatCurrPvaAssistConn,
		ltmPoolStatConnqDepth,
		ltmPoolStatConnqAgeHead,
		ltmPoolStatConnqAgeMax,
		ltmPoolStatConnqAgeEma,
		ltmPoolStatConnqAgeEdm,
		ltmPoolStatConnqServiced,
		ltmPoolStatConnqAllDepth,
		ltmPoolStatConnqAllAgeHead,
		ltmPoolStatConnqAllAgeMax,
		ltmPoolStatConnqAllAgeEma,
		ltmPoolStatConnqAllAgeEdm,
		ltmPoolStatConnqAllServiced,
		ltmPoolStatTotRequests,
		ltmPoolStatCurSessions,
		ltmPoolStatMsgMrIn,
		ltmPoolStatMsgMrOut,
		ltmPoolStatReqMrIn,
		ltmPoolStatReqMrOut,
		ltmPoolStatRespMrIn,
		ltmPoolStatRespMrOut
	}
	STATUS	 current
	DESCRIPTION
		"A collection of objects of ltmPoolStat MIB."
	::= { bigipLocalTMGroups 12 }

ltmPoolMemberGroup OBJECT-GROUP
	 OBJECTS {
		ltmPoolMemberNumber,
		ltmPoolMemberPoolName,
		ltmPoolMemberAddrType,
		ltmPoolMemberAddr,
		ltmPoolMemberPort,
		ltmPoolMemberConnLimit,
		ltmPoolMemberRatio,
		ltmPoolMemberWeight,
		ltmPoolMemberPriority,
		ltmPoolMemberDynamicRatio,
		ltmPoolMemberMonitorState,
		ltmPoolMemberMonitorStatus,
		ltmPoolMemberNewSessionEnable,
		ltmPoolMemberSessionStatus,
		ltmPoolMemberMonitorRule,
		ltmPoolMemberAvailabilityState,
		ltmPoolMemberEnabledState,
		ltmPoolMemberDisabledParentType,
		ltmPoolMemberStatusReason,
		ltmPoolMemberNodeName
	}
	STATUS	 current
	DESCRIPTION
		"A collection of objects of ltmPoolMember MIB."
	::= { bigipLocalTMGroups 13 }

ltmPoolMemberStatGroup OBJECT-GROUP
	 OBJECTS {
		ltmPoolMemberStatResetStats,
		ltmPoolMemberStatNumber,
		ltmPoolMemberStatPoolName,
		ltmPoolMemberStatAddrType,
		ltmPoolMemberStatAddr,
		ltmPoolMemberStatPort,
		ltmPoolMemberStatServerPktsIn,
		ltmPoolMemberStatServerBytesIn,
		ltmPoolMemberStatServerPktsOut,
		ltmPoolMemberStatServerBytesOut,
		ltmPoolMemberStatServerMaxConns,
		ltmPoolMemberStatServerTotConns,
		ltmPoolMemberStatServerCurConns,
		ltmPoolMemberStatPvaPktsIn,
		ltmPoolMemberStatPvaBytesIn,
		ltmPoolMemberStatPvaPktsOut,
		ltmPoolMemberStatPvaBytesOut,
		ltmPoolMemberStatPvaMaxConns,
		ltmPoolMemberStatPvaTotConns,
		ltmPoolMemberStatPvaCurConns,
		ltmPoolMemberStatTotRequests,
		ltmPoolMemberStatTotPvaAssistConn,
		ltmPoolMemberStatCurrPvaAssistConn,
		ltmPoolMemberStatConnqDepth,
		ltmPoolMemberStatConnqAgeHead,
		ltmPoolMemberStatConnqAgeMax,
		ltmPoolMemberStatConnqAgeEma,
		ltmPoolMemberStatConnqAgeEdm,
		ltmPoolMemberStatConnqServiced,
		ltmPoolMemberStatNodeName,
		ltmPoolMemberStatCurSessions,
		ltmPoolMemberStatCurrentConnsPerSec,
		ltmPoolMemberStatDurationRateExceeded,
		ltmPoolMemberStatMsgMrIn,
		ltmPoolMemberStatMsgMrOut,
		ltmPoolMemberStatReqMrIn,
		ltmPoolMemberStatReqMrOut,
		ltmPoolMemberStatRespMrIn,
		ltmPoolMemberStatRespMrOut
	}
	STATUS	 current
	DESCRIPTION
		"A collection of objects of ltmPoolMemberStat MIB."
	::= { bigipLocalTMGroups 14 }

ltmAuthProfileGroup OBJECT-GROUP
	 OBJECTS {
		ltmAuthProfileNumber,
		ltmAuthProfileName,
		ltmAuthProfileConfigSource,
		ltmAuthProfileDefaultName,
		ltmAuthProfileConfigName,
		ltmAuthProfileType,
		ltmAuthProfileMode,
		ltmAuthProfileCredentialSource,
		ltmAuthProfileRuleName,
		ltmAuthProfileIdleTimeout
	}
	STATUS	 current
	DESCRIPTION
		"A collection of objects of ltmAuthProfile MIB."
	::= { bigipLocalTMGroups 15 }

ltmAuthProfileStatGroup OBJECT-GROUP
	 OBJECTS {
		ltmAuthProfileStatResetStats,
		ltmAuthProfileStatNumber,
		ltmAuthProfileStatName,
		ltmAuthProfileStatTotSessions,
		ltmAuthProfileStatCurSessions,
		ltmAuthProfileStatMaxSessions,
		ltmAuthProfileStatSuccessResults,
		ltmAuthProfileStatFailureResults,
		ltmAuthProfileStatWantcredentialResults,
		ltmAuthProfileStatErrorResults
	}
	STATUS	 current
	DESCRIPTION
		"A collection of objects of ltmAuthProfileStat MIB."
	::= { bigipLocalTMGroups 16 }

ltmClientSslGroup OBJECT-GROUP
	 OBJECTS {
		ltmClientSslNumber,
		ltmClientSslName,
		ltmClientSslConfigSource,
		ltmClientSslDefaultName,
		ltmClientSslMode,
		ltmClientSslKey,
		ltmClientSslCert,
		ltmClientSslChain,
		ltmClientSslCafile,
		ltmClientSslCrlfile,
		ltmClientSslClientcertca,
		ltmClientSslCiphers,
		ltmClientSslPassphrase,
		ltmClientSslOptions,
		ltmClientSslModsslmethods,
		ltmClientSslCacheSize,
		ltmClientSslCacheTimeout,
		ltmClientSslRenegotiatePeriod,
		ltmClientSslRenegotiateSize,
		ltmClientSslRenegotiateMaxRecordDelay,
		ltmClientSslHandshakeTimeout,
		ltmClientSslAlertTimeout,
		ltmClientSslPeerCertMode,
		ltmClientSslAuthenticateOnce,
		ltmClientSslAuthenticateDepth,
		ltmClientSslUncleanShutdown,
		ltmClientSslStrictResume,
		ltmClientSslAllowNonssl,
		ltmClientSslSessionTicket,
		ltmClientSslFwdpEnabled,
		ltmClientSslFwdpCaKey,
		ltmClientSslFwdpCaCert,
		ltmClientSslFwdpCaPassphrase,
		ltmClientSslFwdpCertLifespan,
		ltmClientSslFwdpCertExtensionIncludes,
		ltmClientSslFwdpLookupByIpaddrPort,
		ltmClientSslGenericAlert,
		ltmClientSslSslSignHash,
		ltmClientSslFwdpBypassEnabled,
		ltmClientSslFwdpBypassDipBList,
		ltmClientSslFwdpBypassDipWList,
		ltmClientSslFwdpBypassSipBList,
		ltmClientSslFwdpBypassSipWList,
		ltmClientSslFwdpBypassHnBList,
		ltmClientSslFwdpBypassHnWList,
		ltmClientSslProxySsl,
		ltmClientSslProxySslPassthrough,
		ltmClientSslPeerNoRenegotiateTimeout,
		ltmClientSslMaxRenegotiationsPerMin,
		ltmClientSslSessionMirroring,
		ltmClientSslMaxAggregateRenegotiationsPerMin,
		ltmClientSslSessionTicketTimeout,
		ltmClientSslAllowExpiredCrl,
		ltmClientSslMaxActiveHandshake,
		ltmClientSslAllowDynamicRecordSizing,
		ltmClientSslMaximumRecordSize,
		ltmClientSslBypassHsAlertEnabled,
		ltmClientSslBypassClientCertFailEnabled,
		ltmClientSslOcspStapling,
		ltmClientSslNotifyCertStatusToVs,
		ltmClientSslC3dEnabled,
		ltmClientSslCentityOcspObjName,
		ltmClientSslDropUnknownOcspStatus,
		ltmClientSslData0rttMode
	}
	STATUS	 current
	DESCRIPTION
		"A collection of objects of ltmClientSslProfile MIB."
	::= { bigipLocalTMGroups 17 }

ltmClientSslStatGroup OBJECT-GROUP
	 OBJECTS {
		ltmClientSslStatResetStats,
		ltmClientSslStatNumber,
		ltmClientSslStatName,
		ltmClientSslStatCurConns,
		ltmClientSslStatMaxConns,
		ltmClientSslStatCurNativeConns,
		ltmClientSslStatMaxNativeConns,
		ltmClientSslStatTotNativeConns,
		ltmClientSslStatCurCompatConns,
		ltmClientSslStatMaxCompatConns,
		ltmClientSslStatTotCompatConns,
		ltmClientSslStatEncryptedBytesIn,
		ltmClientSslStatEncryptedBytesOut,
		ltmClientSslStatDecryptedBytesIn,
		ltmClientSslStatDecryptedBytesOut,
		ltmClientSslStatRecordsIn,
		ltmClientSslStatRecordsOut,
		ltmClientSslStatFullyHwAcceleratedConns,
		ltmClientSslStatPartiallyHwAcceleratedConns,
		ltmClientSslStatNonHwAcceleratedConns,
		ltmClientSslStatPrematureDisconnects,
		ltmClientSslStatMidstreamRenegotiations,
		ltmClientSslStatSessCacheCurEntries,
		ltmClientSslStatSessCacheHits,
		ltmClientSslStatSessCacheLookups,
		ltmClientSslStatSessCacheOverflows,
		ltmClientSslStatSessCacheInvalidations,
		ltmClientSslStatPeercertValid,
		ltmClientSslStatPeercertInvalid,
		ltmClientSslStatPeercertNone,
		ltmClientSslStatHandshakeFailures,
		ltmClientSslStatBadRecords,
		ltmClientSslStatFatalAlerts,
		ltmClientSslStatSslv2,
		ltmClientSslStatSslv3,
		ltmClientSslStatTlsv1,
		ltmClientSslStatAdhKeyxchg,
		ltmClientSslStatDhDssKeyxchg,
		ltmClientSslStatDhRsaKeyxchg,
		ltmClientSslStatDssKeyxchg,
		ltmClientSslStatEdhDssKeyxchg,
		ltmClientSslStatRsaKeyxchg,
		ltmClientSslStatNullBulk,
		ltmClientSslStatAesBulk,
		ltmClientSslStatDesBulk,
		ltmClientSslStatIdeaBulk,
		ltmClientSslStatRc2Bulk,
		ltmClientSslStatRc4Bulk,
		ltmClientSslStatNullDigest,
		ltmClientSslStatMd5Digest,
		ltmClientSslStatShaDigest,
		ltmClientSslStatNotssl,
		ltmClientSslStatEdhRsaKeyxchg,
		ltmClientSslStatSecureHandshakes,
		ltmClientSslStatInsecureHandshakeAccepts,
		ltmClientSslStatInsecureHandshakeRejects,
		ltmClientSslStatInsecureRenegotiationRejects,
		ltmClientSslStatSniRejects,
		ltmClientSslStatTlsv11,
		ltmClientSslStatTlsv12,
		ltmClientSslStatDtlsv1,
		ltmClientSslStatReused,
		ltmClientSslStatReuseFailed,
		ltmClientSslStatEcdheRsaKeyxchg,
		ltmClientSslStatConns,
		ltmClientSslStatCachedCerts,
		ltmClientSslStatEcdhRsaKeyxchg,
		ltmClientSslStatEcdheEcdsaKeyxchg,
		ltmClientSslStatEcdhEcdsaKeyxchg,
		ltmClientSslStatDheDssKeyxchg,
		ltmClientSslStatAesGcmBulk,
		ltmClientSslStatDestinationIpBypasses,
		ltmClientSslStatSourceIpBypasses,
		ltmClientSslStatHostnameBypasses,
		ltmClientSslStatRenegotiationsRejected,
		ltmClientSslStatOcspStaplingConns,
		ltmClientSslStatOcspStaplingResponseStatusErrors,
		ltmClientSslStatOcspStaplingResponseValidationErrors,
		ltmClientSslStatOcspStaplingCertStatusErrors,
		ltmClientSslStatOcspStaplingOcspConnHttpErrors,
		ltmClientSslStatOcspStaplingOcspConnTimeouts,
		ltmClientSslStatOcspStaplingOcspConnFailures,
		ltmClientSslStatAggregateRenegotiationsRejected,
		ltmClientSslStatSessionMirrorSuccess,
		ltmClientSslStatSessionMirrorFailure,
		ltmClientSslStatConnectionMirrorPeerReady,
		ltmClientSslStatConnectionMirrorHaCtxSent,
		ltmClientSslStatConnectionMirrorHaCtxRecv,
		ltmClientSslStatConnectionMirrorHaHsSuccess,
		ltmClientSslStatConnectionMirrorHaFailure,
		ltmClientSslStatConnectionMirrorHaTimeout,
		ltmClientSslStatDtlsTxPushbacks,
		ltmClientSslStatCamelliaBulk,
		ltmClientSslStatActiveHandshakeRejected,
		ltmClientSslStatCurrentActiveHandshakes,
		ltmClientSslStatLicensedTps,
		ltmClientSslStatRecordSize1k,
		ltmClientSslStatRecordSize2k,
		ltmClientSslStatRecordSize3k,
		ltmClientSslStatRecordSize4k,
		ltmClientSslStatRecordSize5k,
		ltmClientSslStatRecordSize6k,
		ltmClientSslStatRecordSize7k,
		ltmClientSslStatRecordSize8k,
		ltmClientSslStatRecordSize9k,
		ltmClientSslStatRecordSize10k,
		ltmClientSslStatRecordSize11k,
		ltmClientSslStatRecordSize12k,
		ltmClientSslStatRecordSize13k,
		ltmClientSslStatRecordSize14k,
		ltmClientSslStatRecordSize15k,
		ltmClientSslStatRecordSize16k,
		ltmClientSslStatExtendedMasterSecrets,
		ltmClientSslStatBypassesHandshakeAlert,
		ltmClientSslStatBypassClientCertificateRequest,
		ltmClientSslStatOcspFwdpClientsslCachedResp,
		ltmClientSslStatOcspFwdpClientsslCertStatusReq,
		ltmClientSslStatOcspFwdpClientsslStapledResp,
		ltmClientSslStatOcspFwdpClientsslRespstatusErrResp,
		ltmClientSslStatOcspFwdpClientsslInvalidCertResp,
		ltmClientSslStatOcspFwdpClientsslRevokedResp,
		ltmClientSslStatOcspFwdpClientsslUnknownResp,
		ltmClientSslStatC3dConns,
		ltmClientSslStatTlsv13,
		ltmClientSslStatChacha20Poly1305Bulk,
		ltmClientSslStatData0rttAccepts,
		ltmClientSslStatData0rttRejects,
		ltmClientSslStatAesBulkOffload,
		ltmClientSslStatAesGcmBulkOffload,
		ltmClientSslStatChacha20Poly1305BulkOffld,
		ltmClientSslStatDesBulkOffload,
		ltmClientSslStatRc4BulkOffload,
		ltmClientSslStatCamelliaBulkOffload,
		ltmClientSslStatMd5DigestOffload,
		ltmClientSslStatShaDigestOffload,
		ltmClientSslStatSha224Digest,
		ltmClientSslStatSha224DigestOffload,
		ltmClientSslStatSha256Digest,
		ltmClientSslStatSha256DigestOffload,
		ltmClientSslStatSha384Digest,
		ltmClientSslStatSha384DigestOffload,
		ltmClientSslStatSha512Digest,
		ltmClientSslStatSha512DigestOffload,
		ltmClientSslStatDhGroupP256,
		ltmClientSslStatDhGroupP256Offload,
		ltmClientSslStatDhGroupP384,
		ltmClientSslStatDhGroupP384Offload,
		ltmClientSslStatDhGroupX25519,
		ltmClientSslStatDhGroupX25519Offload,
		ltmClientSslStatRsaKeySize1024,
		ltmClientSslStatRsaKeySize1024Offload,
		ltmClientSslStatRsaKeySize2048,
		ltmClientSslStatRsaKeySize2048Offload,
		ltmClientSslStatRsaKeySize4096,
		ltmClientSslStatRsaKeySize4096Offload,
		ltmClientSslStatTotalHandshakesSoftware,
		ltmClientSslStatTotalHandshakesOffload
	}
	STATUS	 current
	DESCRIPTION
		"A collection of objects of ltmClientSslProfileStat MIB."
	::= { bigipLocalTMGroups 18 }

ltmServerSslGroup OBJECT-GROUP
	 OBJECTS {
		ltmServerSslNumber,
		ltmServerSslName,
		ltmServerSslConfigSource,
		ltmServerSslDefaultName,
		ltmServerSslMode,
		ltmServerSslKey,
		ltmServerSslCert,
		ltmServerSslChain,
		ltmServerSslCafile,
		ltmServerSslCrlfile,
		ltmServerSslCiphers,
		ltmServerSslPassphrase,
		ltmServerSslOptions,
		ltmServerSslModsslmethods,
		ltmServerSslRenegotiatePeriod,
		ltmServerSslRenegotiateSize,
		ltmServerSslPeerCertMode,
		ltmServerSslAuthenticateOnce,
		ltmServerSslAuthenticateDepth,
		ltmServerSslAuthenticateName,
		ltmServerSslUncleanShutdown,
		ltmServerSslStrictResume,
		ltmServerSslHandshakeTimeout,
		ltmServerSslAlertTimeout,
		ltmServerSslCacheSize,
		ltmServerSslCacheTimeout,
		ltmServerSslSessionTicket,
		ltmServerSslFwdpEnabled,
		ltmServerSslDropExpCert,
		ltmServerSslDropUntrustCa,
		ltmServerSslGenericAlert,
		ltmServerSslSslSignHash,
		ltmServerSslFwdpBypassEnabled,
		ltmServerSslProxySsl,
		ltmServerSslProxySslPassthrough,
		ltmServerSslSessionMirroring,
		ltmServerSslAllowExpiredCrl,
		ltmServerSslMaxActiveHandshake,
		ltmServerSslBypassHsAlertEnabled,
		ltmServerSslBypassClientCertFailEnabled,
		ltmServerSslCentityOcspObjName,
		ltmServerSslC3dEnabled,
		ltmServerSslC3dCaKey,
		ltmServerSslC3dCaCert,
		ltmServerSslC3dCaPassphrase,
		ltmServerSslC3dCertLifespan,
		ltmServerSslC3dCertExtensionIncludes,
		ltmServerSslData0rttMode
	}
	STATUS	 current
	DESCRIPTION
		"A collection of objects of ltmServerSslProfile MIB."
	::= { bigipLocalTMGroups 19 }

ltmServerSslStatGroup OBJECT-GROUP
	 OBJECTS {
		ltmServerSslStatResetStats,
		ltmServerSslStatNumber,
		ltmServerSslStatName,
		ltmServerSslStatCurConns,
		ltmServerSslStatMaxConns,
		ltmServerSslStatCurNativeConns,
		ltmServerSslStatMaxNativeConns,
		ltmServerSslStatTotNativeConns,
		ltmServerSslStatCurCompatConns,
		ltmServerSslStatMaxCompatConns,
		ltmServerSslStatTotCompatConns,
		ltmServerSslStatEncryptedBytesIn,
		ltmServerSslStatEncryptedBytesOut,
		ltmServerSslStatDecryptedBytesIn,
		ltmServerSslStatDecryptedBytesOut,
		ltmServerSslStatRecordsIn,
		ltmServerSslStatRecordsOut,
		ltmServerSslStatFullyHwAcceleratedConns,
		ltmServerSslStatPartiallyHwAcceleratedConns,
		ltmServerSslStatNonHwAcceleratedConns,
		ltmServerSslStatPrematureDisconnects,
		ltmServerSslStatMidstreamRenegotiations,
		ltmServerSslStatSessCacheCurEntries,
		ltmServerSslStatSessCacheHits,
		ltmServerSslStatSessCacheLookups,
		ltmServerSslStatSessCacheOverflows,
		ltmServerSslStatSessCacheInvalidations,
		ltmServerSslStatPeercertValid,
		ltmServerSslStatPeercertInvalid,
		ltmServerSslStatPeercertNone,
		ltmServerSslStatHandshakeFailures,
		ltmServerSslStatBadRecords,
		ltmServerSslStatFatalAlerts,
		ltmServerSslStatSslv2,
		ltmServerSslStatSslv3,
		ltmServerSslStatTlsv1,
		ltmServerSslStatAdhKeyxchg,
		ltmServerSslStatDhDssKeyxchg,
		ltmServerSslStatDhRsaKeyxchg,
		ltmServerSslStatDssKeyxchg,
		ltmServerSslStatEdhDssKeyxchg,
		ltmServerSslStatRsaKeyxchg,
		ltmServerSslStatNullBulk,
		ltmServerSslStatAesBulk,
		ltmServerSslStatDesBulk,
		ltmServerSslStatIdeaBulk,
		ltmServerSslStatRc2Bulk,
		ltmServerSslStatRc4Bulk,
		ltmServerSslStatNullDigest,
		ltmServerSslStatMd5Digest,
		ltmServerSslStatShaDigest,
		ltmServerSslStatNotssl,
		ltmServerSslStatEdhRsaKeyxchg,
		ltmServerSslStatSecureHandshakes,
		ltmServerSslStatInsecureHandshakeAccepts,
		ltmServerSslStatInsecureHandshakeRejects,
		ltmServerSslStatInsecureRenegotiationRejects,
		ltmServerSslStatSniRejects,
		ltmServerSslStatTlsv11,
		ltmServerSslStatTlsv12,
		ltmServerSslStatDtlsv1,
		ltmServerSslStatReused,
		ltmServerSslStatReuseFailed,
		ltmServerSslStatEcdheRsaKeyxchg,
		ltmServerSslStatConns,
		ltmServerSslStatEcdhRsaKeyxchg,
		ltmServerSslStatEcdheEcdsaKeyxchg,
		ltmServerSslStatEcdhEcdsaKeyxchg,
		ltmServerSslStatDheDssKeyxchg,
		ltmServerSslStatAesGcmBulk,
		ltmServerSslStatDestinationIpBypasses,
		ltmServerSslStatSourceIpBypasses,
		ltmServerSslStatHostnameBypasses,
		ltmServerSslStatSessionMirrorSuccess,
		ltmServerSslStatSessionMirrorFailure,
		ltmServerSslStatConnectionMirrorPeerReady,
		ltmServerSslStatConnectionMirrorHaCtxSent,
		ltmServerSslStatConnectionMirrorHaCtxRecv,
		ltmServerSslStatConnectionMirrorHaHsSuccess,
		ltmServerSslStatConnectionMirrorHaFailure,
		ltmServerSslStatConnectionMirrorHaTimeout,
		ltmServerSslStatDtlsTxPushbacks,
		ltmServerSslStatCamelliaBulk,
		ltmServerSslStatActiveHandshakeRejected,
		ltmServerSslStatCurrentActiveHandshakes,
		ltmServerSslStatLicensedTps,
		ltmServerSslStatExtendedMasterSecrets,
		ltmServerSslStatOcspServersslCachedResp,
		ltmServerSslStatOcspServersslStapledResp,
		ltmServerSslStatOcspServersslResponderQueries,
		ltmServerSslStatOcspServersslResponseErrors,
		ltmServerSslStatOcspServersslCertStatusUnknown,
		ltmServerSslStatOcspServersslCertStatusRevoked,
		ltmServerSslStatC3dConns,
		ltmServerSslStatTlsv13,
		ltmServerSslStatChacha20Poly1305Bulk,
		ltmServerSslStatAesBulkOffload,
		ltmServerSslStatAesGcmBulkOffload,
		ltmServerSslStatChacha20Poly1305BulkOffld,
		ltmServerSslStatDesBulkOffload,
		ltmServerSslStatRc4BulkOffload,
		ltmServerSslStatCamelliaBulkOffload,
		ltmServerSslStatMd5DigestOffload,
		ltmServerSslStatShaDigestOffload,
		ltmServerSslStatSha224Digest,
		ltmServerSslStatSha224DigestOffload,
		ltmServerSslStatSha256Digest,
		ltmServerSslStatSha256DigestOffload,
		ltmServerSslStatSha384Digest,
		ltmServerSslStatSha384DigestOffload,
		ltmServerSslStatSha512Digest,
		ltmServerSslStatSha512DigestOffload,
		ltmServerSslStatDhGroupP256,
		ltmServerSslStatDhGroupP256Offload,
		ltmServerSslStatDhGroupP384,
		ltmServerSslStatDhGroupP384Offload,
		ltmServerSslStatDhGroupX25519,
		ltmServerSslStatDhGroupX25519Offload,
		ltmServerSslStatRsaKeySize1024,
		ltmServerSslStatRsaKeySize1024Offload,
		ltmServerSslStatRsaKeySize2048,
		ltmServerSslStatRsaKeySize2048Offload,
		ltmServerSslStatRsaKeySize4096,
		ltmServerSslStatRsaKeySize4096Offload,
		ltmServerSslStatTotalHandshakesSoftware,
		ltmServerSslStatTotalHandshakesOffload
	}
	STATUS	 current
	DESCRIPTION
		"A collection of objects of ltmServerSslProfileStat MIB."
	::= { bigipLocalTMGroups 20 }

ltmConnPoolProfileGroup OBJECT-GROUP
	 OBJECTS {
		ltmConnPoolProfileNumber,
		ltmConnPoolProfileName,
		ltmConnPoolProfileConfigSource,
		ltmConnPoolProfileDefaultName,
		ltmConnPoolProfileSrcMaskType,
		ltmConnPoolProfileSrcMask,
		ltmConnPoolProfileMaxSize,
		ltmConnPoolProfileMaxAge,
		ltmConnPoolProfileMaxReuse,
		ltmConnPoolProfileIdleTimeout
	}
	STATUS	 current
	DESCRIPTION
		"A collection of objects of ltmConnPoolProfile MIB."
	::= { bigipLocalTMGroups 21 }

ltmConnPoolProfileStatGroup OBJECT-GROUP
	 OBJECTS {
		ltmConnPoolProfileStatResetStats,
		ltmConnPoolProfileStatNumber,
		ltmConnPoolProfileStatName,
		ltmConnPoolProfileStatCurSize,
		ltmConnPoolProfileStatMaxSize,
		ltmConnPoolProfileStatReuses,
		ltmConnPoolProfileStatConnects
	}
	STATUS	 current
	DESCRIPTION
		"A collection of objects of ltmConnPoolProfileStat MIB."
	::= { bigipLocalTMGroups 22 }

ltmFastL4ProfileGroup OBJECT-GROUP
	 OBJECTS {
		ltmFastL4ProfileNumber,
		ltmFastL4ProfileName,
		ltmFastL4ProfileConfigSource,
		ltmFastL4ProfileDefaultName,
		ltmFastL4ProfileResetOnTimeout,
		ltmFastL4ProfileIpFragReass,
		ltmFastL4ProfileIdleTimeout,
		ltmFastL4ProfileTcpHandshakeTimeout,
		ltmFastL4ProfileMssOverride,
		ltmFastL4ProfilePvaAccelMode,
		ltmFastL4ProfileTcpTimestampMode,
		ltmFastL4ProfileTcpWscaleMode,
		ltmFastL4ProfileTcpGenerateIsn,
		ltmFastL4ProfileTcpStripSack,
		ltmFastL4ProfileIpTosToClient,
		ltmFastL4ProfileIpTosToServer,
		ltmFastL4ProfileLinkQosToClient,
		ltmFastL4ProfileLinkQosToServer,
		ltmFastL4ProfileRttFromClient,
		ltmFastL4ProfileRttFromServer,
		ltmFastL4ProfileTcpCloseTimeout,
		ltmFastL4ProfileLooseInitiation,
		ltmFastL4ProfileLooseClose,
		ltmFastL4ProfileHardSyncookie,
		ltmFastL4ProfileSoftSyncookie,
		ltmFastL4ProfileLateBinding,
		ltmFastL4ProfileExplicitFlowMigration,
		ltmFastL4ProfileClientTimeout,
		ltmFastL4ProfileTimeoutRecovery
	}
	STATUS	 current
	DESCRIPTION
		"A collection of objects of ltmFastL4Profile MIB."
	::= { bigipLocalTMGroups 23 }

ltmFtpProfileGroup OBJECT-GROUP
	 OBJECTS {
		ltmFtpProfileNumber,
		ltmFtpProfileName,
		ltmFtpProfileConfigSource,
		ltmFtpProfileDefaultName,
		ltmFtpProfileTranslateExtended,
		ltmFtpProfileDataPort,
		ltmFtpProfileLogPublisher,
		ltmFtpProfileLogProfile
	}
	STATUS	 current
	DESCRIPTION
		"A collection of objects of ltmFtpProfile MIB."
	::= { bigipLocalTMGroups 24 }

ltmHttpProfileGroup OBJECT-GROUP
	 OBJECTS {
		ltmHttpProfileNumber,
		ltmHttpProfileName,
		ltmHttpProfileConfigSource,
		ltmHttpProfileDefaultName,
		ltmHttpProfileBasicAuthRealm,
		ltmHttpProfileOneConnect,
		ltmHttpProfileHeaderInsert,
		ltmHttpProfileHeaderErase,
		ltmHttpProfileFallbackHost,
		ltmHttpProfileCompressMode,
		ltmHttpProfileCompressMinSize,
		ltmHttpProfileCompressBufferSize,
		ltmHttpProfileCompressVaryHeader,
		ltmHttpProfileCompressAllowHttp10,
		ltmHttpProfileCompressGzipMemlevel,
		ltmHttpProfileCompressGzipWindowsize,
		ltmHttpProfileCompressGzipLevel,
		ltmHttpProfileCompressKeepAcceptEncoding,
		ltmHttpProfileCompressBrowserWorkarounds,
		ltmHttpProfileRequestChunking,
		ltmHttpProfileResponseChunking,
		ltmHttpProfileLwsMaxColumn,
		ltmHttpProfileLwsSeparator,
		ltmHttpProfileRedirectRewrite,
		ltmHttpProfileMaxHeaderSize,
		ltmHttpProfilePipelining,
		ltmHttpProfileInsertXforwardedFor,
		ltmHttpProfileMaxRequests,
		ltmHttpProfileCompressCpusaver,
		ltmHttpProfileCompressCpusaverHigh,
		ltmHttpProfileCompressCpusaverLow,
		ltmHttpProfileRamcache,
		ltmHttpProfileRamcacheSize,
		ltmHttpProfileRamcacheMaxEntries,
		ltmHttpProfileRamcacheMaxAge,
		ltmHttpProfileRamcacheObjectMinSize,
		ltmHttpProfileRamcacheObjectMaxSize,
		ltmHttpProfileRamcacheIgnoreClient,
		ltmHttpProfileRamcacheAgingRate,
		ltmHttpProfileRamcacheInsertAgeHeader,
		ltmHttpProfileCompressPreferredMethod,
		ltmHttpProfileServerAgentName,
		ltmHttpProfilePassthroughPipeline,
		ltmHttpProfileTruncatedRedirects,
		ltmHttpProfilePassthroughOversizeClientHeaders,
		ltmHttpProfilePassthroughOversizeServerHeaders,
		ltmHttpProfilePassthroughExcessClientHeaders,
		ltmHttpProfilePassthroughExcessServerHeaders,
		ltmHttpProfilePassthroughUnknownMethod,
		ltmHttpProfileHstsMode,
		ltmHttpProfileHstsMaximumAge,
		ltmHttpProfileHstsIncludeSubdomains,
		ltmHttpProfileHstsPreload,
		ltmHttpProfileOneConnectStatusReuse
	}
	STATUS	 current
	DESCRIPTION
		"A collection of objects of ltmHttpProfile MIB."
	::= { bigipLocalTMGroups 25 }

ltmCompUriInclGroup OBJECT-GROUP
	 OBJECTS {
		ltmCompUriInclNumber,
		ltmCompUriInclName,
		ltmCompUriInclIndex,
		ltmCompUriInclUri
	}
	STATUS	 current
	DESCRIPTION
		"A collection of objects of ltmHttpProfileCompUriIncl MIB."
	::= { bigipLocalTMGroups 26 }

ltmCompUriExclGroup OBJECT-GROUP
	 OBJECTS {
		ltmCompUriExclNumber,
		ltmCompUriExclName,
		ltmCompUriExclIndex,
		ltmCompUriExclUri
	}
	STATUS	 current
	DESCRIPTION
		"A collection of objects of ltmHttpProfileCompUriExcl MIB."
	::= { bigipLocalTMGroups 27 }

ltmCompContTypeInclGroup OBJECT-GROUP
	 OBJECTS {
		ltmCompContTypeInclNumber,
		ltmCompContTypeInclName,
		ltmCompContTypeInclIndex,
		ltmCompContTypeInclContentType
	}
	STATUS	 current
	DESCRIPTION
		"A collection of objects of ltmHttpProfileCompContTypeIncl MIB."
	::= { bigipLocalTMGroups 28 }

ltmCompContTypeExclGroup OBJECT-GROUP
	 OBJECTS {
		ltmCompContTypeExclNumber,
		ltmCompContTypeExclName,
		ltmCompContTypeExclIndex,
		ltmCompContTypeExclContentType
	}
	STATUS	 current
	DESCRIPTION
		"A collection of objects of ltmHttpProfileCompContTypeExcl MIB."
	::= { bigipLocalTMGroups 29 }

ltmHttpProfileStatGroup OBJECT-GROUP
	 OBJECTS {
		ltmHttpProfileStatResetStats,
		ltmHttpProfileStatNumber,
		ltmHttpProfileStatName,
		ltmHttpProfileStatCookiePersistInserts,
		ltmHttpProfileStatResp2xxCnt,
		ltmHttpProfileStatResp3xxCnt,
		ltmHttpProfileStatResp4xxCnt,
		ltmHttpProfileStatResp5xxCnt,
		ltmHttpProfileStatNumberReqs,
		ltmHttpProfileStatGetReqs,
		ltmHttpProfileStatPostReqs,
		ltmHttpProfileStatV9Reqs,
		ltmHttpProfileStatV10Reqs,
		ltmHttpProfileStatV11Reqs,
		ltmHttpProfileStatV9Resp,
		ltmHttpProfileStatV10Resp,
		ltmHttpProfileStatV11Resp,
		ltmHttpProfileStatMaxKeepaliveReq,
		ltmHttpProfileStatRespBucket1k,
		ltmHttpProfileStatRespBucket4k,
		ltmHttpProfileStatRespBucket16k,
		ltmHttpProfileStatRespBucket32k,
		ltmHttpProfileStatPrecompressBytes,
		ltmHttpProfileStatPostcompressBytes,
		ltmHttpProfileStatNullCompressBytes,
		ltmHttpProfileStatHtmlPrecompressBytes,
		ltmHttpProfileStatHtmlPostcompressBytes,
		ltmHttpProfileStatCssPrecompressBytes,
		ltmHttpProfileStatCssPostcompressBytes,
		ltmHttpProfileStatJsPrecompressBytes,
		ltmHttpProfileStatJsPostcompressBytes,
		ltmHttpProfileStatXmlPrecompressBytes,
		ltmHttpProfileStatXmlPostcompressBytes,
		ltmHttpProfileStatSgmlPrecompressBytes,
		ltmHttpProfileStatSgmlPostcompressBytes,
		ltmHttpProfileStatPlainPrecompressBytes,
		ltmHttpProfileStatPlainPostcompressBytes,
		ltmHttpProfileStatOctetPrecompressBytes,
		ltmHttpProfileStatOctetPostcompressBytes,
		ltmHttpProfileStatImagePrecompressBytes,
		ltmHttpProfileStatImagePostcompressBytes,
		ltmHttpProfileStatVideoPrecompressBytes,
		ltmHttpProfileStatVideoPostcompressBytes,
		ltmHttpProfileStatAudioPrecompressBytes,
		ltmHttpProfileStatAudioPostcompressBytes,
		ltmHttpProfileStatOtherPrecompressBytes,
		ltmHttpProfileStatOtherPostcompressBytes,
		ltmHttpProfileStatRamcacheHits,
		ltmHttpProfileStatRamcacheMisses,
		ltmHttpProfileStatRamcacheMissesAll,
		ltmHttpProfileStatRamcacheHitBytes,
		ltmHttpProfileStatRamcacheMissBytes,
		ltmHttpProfileStatRamcacheMissBytesAll,
		ltmHttpProfileStatRamcacheSize,
		ltmHttpProfileStatRamcacheCount,
		ltmHttpProfileStatRamcacheEvictions,
		ltmHttpProfileStatRespBucket64k,
		ltmHttpProfileStatPassthroughIrule,
		ltmHttpProfileStatPassthroughConnect,
		ltmHttpProfileStatPassthroughWebSockets,
		ltmHttpProfileStatPassthroughOversizeClientHeaders,
		ltmHttpProfileStatPassthroughOversizeServerHeaders,
		ltmHttpProfileStatPassthroughExcessClientHeaders,
		ltmHttpProfileStatPassthroughExcessServerHeaders,
		ltmHttpProfileStatPassthroughUnknownMethod,
		ltmHttpProfileStatPassthroughPipeline
	}
	STATUS	 current
	DESCRIPTION
		"A collection of objects of ltmHttpProfileStat MIB."
	::= { bigipLocalTMGroups 30 }

ltmPersistProfileGroup OBJECT-GROUP
	 OBJECTS {
		ltmPersistProfileNumber,
		ltmPersistProfileName,
		ltmPersistProfileConfigSource,
		ltmPersistProfileDefaultName,
		ltmPersistProfileMode,
		ltmPersistProfileMirror,
		ltmPersistProfileTimeout,
		ltmPersistProfileMaskType,
		ltmPersistProfileMask,
		ltmPersistProfileCookieMethod,
		ltmPersistProfileCookieName,
		ltmPersistProfileCookieExpiration,
		ltmPersistProfileCookieHashOffset,
		ltmPersistProfileCookieHashLength,
		ltmPersistProfileMsrdpNoSessionDir,
		ltmPersistProfileMapProxies,
		ltmPersistProfileAcrossServices,
		ltmPersistProfileAcrossVirtuals,
		ltmPersistProfileAcrossPools,
		ltmPersistProfileUieRule,
		ltmPersistProfileSipInfo,
		ltmPersistProfileCookieHttpOnly,
		ltmPersistProfileCookieSecure
	}
	STATUS	 current
	DESCRIPTION
		"A collection of objects of ltmPersistProfile MIB."
	::= { bigipLocalTMGroups 31 }

ltmStreamProfileGroup OBJECT-GROUP
	 OBJECTS {
		ltmStreamProfileNumber,
		ltmStreamProfileName,
		ltmStreamProfileConfigSource,
		ltmStreamProfileDefaultName,
		ltmStreamProfileSource,
		ltmStreamProfileTarget
	}
	STATUS	 current
	DESCRIPTION
		"A collection of objects of ltmStreamProfile MIB."
	::= { bigipLocalTMGroups 32 }

ltmStreamProfileStatGroup OBJECT-GROUP
	 OBJECTS {
		ltmStreamProfileStatResetStats,
		ltmStreamProfileStatNumber,
		ltmStreamProfileStatName,
		ltmStreamProfileStatReplaces
	}
	STATUS	 current
	DESCRIPTION
		"A collection of objects of ltmStreamProfileStat MIB."
	::= { bigipLocalTMGroups 33 }

ltmTcpProfileGroup OBJECT-GROUP
	 OBJECTS {
		ltmTcpProfileNumber,
		ltmTcpProfileName,
		ltmTcpProfileConfigSource,
		ltmTcpProfileDefaultName,
		ltmTcpProfileResetOnTimeout,
		ltmTcpProfileTimeWaitRecycle,
		ltmTcpProfileDelayedAcks,
		ltmTcpProfileProxyMss,
		ltmTcpProfileProxyOptions,
		ltmTcpProfileProxyBufferLow,
		ltmTcpProfileProxyBufferHigh,
		ltmTcpProfileIdleTimeout,
		ltmTcpProfileTimeWaitTimeout,
		ltmTcpProfileFinWaitTimeout,
		ltmTcpProfileCloseWaitTimeout,
		ltmTcpProfileSndbuf,
		ltmTcpProfileRcvwnd,
		ltmTcpProfileKeepAliveInterval,
		ltmTcpProfileSynMaxrtx,
		ltmTcpProfileMaxrtx,
		ltmTcpProfileIpTosToClient,
		ltmTcpProfileLinkQosToClient,
		ltmTcpProfileDeferredAccept,
		ltmTcpProfileSelectiveAcks,
		ltmTcpProfileEcn,
		ltmTcpProfileLimitedTransmit,
		ltmTcpProfileHighPerfTcpExt,
		ltmTcpProfileSlowStart,
		ltmTcpProfileBandwidthDelay,
		ltmTcpProfileNagle,
		ltmTcpProfileAckOnPush,
		ltmTcpProfileMd5Sig,
		ltmTcpProfileMd5SigPass,
		ltmTcpProfileAbc,
		ltmTcpProfileCongestionCtrl,
		ltmTcpProfileDsack,
		ltmTcpProfileCmetricsCache,
		ltmTcpProfileVerifiedAccept,
		ltmTcpProfilePktLossIgnoreRate,
		ltmTcpProfilePktLossIgnoreBurst,
		ltmTcpProfileZeroWindowTimeout,
		ltmTcpProfileInitCwnd,
		ltmTcpProfileInitRwnd,
		ltmTcpProfileDelayWindowControl,
		ltmTcpProfileSynRtoBase,
		ltmTcpProfileTimestamps,
		ltmTcpProfileMinRto,
		ltmTcpProfileMptcp,
		ltmTcpProfileRatePace,
		ltmTcpProfileMptcpCsum,
		ltmTcpProfileMptcpCsumVerify,
		ltmTcpProfileMptcpDebug,
		ltmTcpProfileMptcpFallback,
		ltmTcpProfileMptcpJoinmax,
		ltmTcpProfileMptcpNojoindssack,
		ltmTcpProfileMptcpRtomax,
		ltmTcpProfileMptcpRxmitmin,
		ltmTcpProfileMptcpSubflowmax,
		ltmTcpProfileMptcpMakeafterbreak,
		ltmTcpProfileMptcpTimeout,
		ltmTcpProfileMptcpFastjoin,
		ltmTcpProfileEarlyRetransmit,
		ltmTcpProfileTailLossProbe,
		ltmTcpProfileCmetricsCacheTimeout,
		ltmTcpProfileRatePaceMaxRate,
		ltmTcpProfileFastOpen,
		ltmTcpProfileFastOpenCookieExpiration,
		ltmTcpProfileFinWait2Timeout,
		ltmTcpProfileRexmtThresh,
		ltmTcpProfileAutoSendBuffer,
		ltmTcpProfileAutoReceiveWindow,
		ltmTcpProfileAutoProxyBuffer,
		ltmTcpProfileEnhancedLossRecovery,
		ltmTcpProfilePushFlag
	}
	STATUS	 current
	DESCRIPTION
		"A collection of objects of ltmTcpProfile MIB."
	::= { bigipLocalTMGroups 34 }

ltmTcpProfileStatGroup OBJECT-GROUP
	 OBJECTS {
		ltmTcpProfileStatResetStats,
		ltmTcpProfileStatNumber,
		ltmTcpProfileStatName,
		ltmTcpProfileStatOpen,
		ltmTcpProfileStatCloseWait,
		ltmTcpProfileStatFinWait,
		ltmTcpProfileStatTimeWait,
		ltmTcpProfileStatAccepts,
		ltmTcpProfileStatAcceptfails,
		ltmTcpProfileStatConnects,
		ltmTcpProfileStatConnfails,
		ltmTcpProfileStatExpires,
		ltmTcpProfileStatAbandons,
		ltmTcpProfileStatRxrst,
		ltmTcpProfileStatRxbadsum,
		ltmTcpProfileStatRxbadseg,
		ltmTcpProfileStatRxooseg,
		ltmTcpProfileStatRxcookie,
		ltmTcpProfileStatRxbadcookie,
		ltmTcpProfileStatSyncacheover,
		ltmTcpProfileStatTxrexmits,
		ltmTcpProfileStatFinWait2
	}
	STATUS	 current
	DESCRIPTION
		"A collection of objects of ltmTcpProfileStat MIB."
	::= { bigipLocalTMGroups 35 }

ltmUdpProfileGroup OBJECT-GROUP
	 OBJECTS {
		ltmUdpProfileNumber,
		ltmUdpProfileName,
		ltmUdpProfileConfigSource,
		ltmUdpProfileDefaultName,
		ltmUdpProfileIdleTimeout,
		ltmUdpProfileIpTosToClient,
		ltmUdpProfileLinkQosToClient,
		ltmUdpProfileDatagramLb,
		ltmUdpProfileAllowNoPayload,
		ltmUdpProfileSndbuf
	}
	STATUS	 current
	DESCRIPTION
		"A collection of objects of ltmUdpProfile MIB."
	::= { bigipLocalTMGroups 36 }

ltmUdpProfileStatGroup OBJECT-GROUP
	 OBJECTS {
		ltmUdpProfileStatResetStats,
		ltmUdpProfileStatNumber,
		ltmUdpProfileStatName,
		ltmUdpProfileStatOpen,
		ltmUdpProfileStatAccepts,
		ltmUdpProfileStatAcceptfails,
		ltmUdpProfileStatConnects,
		ltmUdpProfileStatConnfails,
		ltmUdpProfileStatExpires,
		ltmUdpProfileStatRxdgram,
		ltmUdpProfileStatRxbaddgram,
		ltmUdpProfileStatRxunreach,
		ltmUdpProfileStatRxbadsum,
		ltmUdpProfileStatRxnosum,
		ltmUdpProfileStatTxdgram
	}
	STATUS	 current
	DESCRIPTION
		"A collection of objects of ltmUdpProfileStat MIB."
	::= { bigipLocalTMGroups 37 }

ltmRuleGroup OBJECT-GROUP
	 OBJECTS {
		ltmRuleNumber,
		ltmRuleName,
		ltmRuleDefinition,
		ltmRuleConfigSource
	}
	STATUS	 current
	DESCRIPTION
		"A collection of objects of ltmRule MIB."
	::= { bigipLocalTMGroups 38 }

ltmRuleEventGroup OBJECT-GROUP
	 OBJECTS {
		ltmRuleEventNumber,
		ltmRuleEventName,
		ltmRuleEventEventType,
		ltmRuleEventPriority,
		ltmRuleEventScript
	}
	STATUS	 current
	DESCRIPTION
		"A collection of objects of ltmRuleEvent MIB."
	::= { bigipLocalTMGroups 39 }

ltmRuleEventStatGroup OBJECT-GROUP
	 OBJECTS {
		ltmRuleEventStatResetStats,
		ltmRuleEventStatNumber,
		ltmRuleEventStatName,
		ltmRuleEventStatEventType,
		ltmRuleEventStatPriority,
		ltmRuleEventStatFailures,
		ltmRuleEventStatAborts,
		ltmRuleEventStatTotalExecutions,
		ltmRuleEventStatAvgCycles,
		ltmRuleEventStatMaxCycles,
		ltmRuleEventStatMinCycles
	}
	STATUS	 current
	DESCRIPTION
		"A collection of objects of ltmRuleEventStat MIB."
	::= { bigipLocalTMGroups 40 }

ltmSnatGroup OBJECT-GROUP
	 OBJECTS {
		ltmSnatNumber,
		ltmSnatName,
		ltmSnatSfFlags,
		ltmSnatType,
		ltmSnatTransAddrType,
		ltmSnatTransAddr,
		ltmSnatSnatpoolName,
		ltmSnatListedEnabledVlans,
		ltmSnatTransAddrName
	}
	STATUS	 current
	DESCRIPTION
		"A collection of objects of ltmSnat MIB."
	::= { bigipLocalTMGroups 41 }

ltmSnatStatGroup OBJECT-GROUP
	 OBJECTS {
		ltmSnatStatResetStats,
		ltmSnatStatNumber,
		ltmSnatStatName,
		ltmSnatStatClientPktsIn,
		ltmSnatStatClientBytesIn,
		ltmSnatStatClientPktsOut,
		ltmSnatStatClientBytesOut,
		ltmSnatStatClientMaxConns,
		ltmSnatStatClientTotConns,
		ltmSnatStatClientCurConns
	}
	STATUS	 current
	DESCRIPTION
		"A collection of objects of ltmSnatStat MIB."
	::= { bigipLocalTMGroups 42 }

ltmSnatVlanGroup OBJECT-GROUP
	 OBJECTS {
		ltmSnatVlanNumber,
		ltmSnatVlanSnatName,
		ltmSnatVlanVlanName
	}
	STATUS	 current
	DESCRIPTION
		"A collection of objects of ltmSnatVlan MIB."
	::= { bigipLocalTMGroups 43 }

ltmSnatOrigAddrGroup OBJECT-GROUP
	 OBJECTS {
		ltmSnatOrigAddrNumber,
		ltmSnatOrigAddrSnatName,
		ltmSnatOrigAddrAddrType,
		ltmSnatOrigAddrAddr,
		ltmSnatOrigAddrWildmaskType,
		ltmSnatOrigAddrWildmask
	}
	STATUS	 current
	DESCRIPTION
		"A collection of objects of ltmSnatOrigAddr MIB."
	::= { bigipLocalTMGroups 44 }

ltmTransAddrGroup OBJECT-GROUP
	 OBJECTS {
		ltmTransAddrNumber,
		ltmTransAddrAddrType,
		ltmTransAddrAddr,
		ltmTransAddrEnabled,
		ltmTransAddrConnLimit,
		ltmTransAddrTcpIdleTimeout,
		ltmTransAddrUdpIdleTimeout,
		ltmTransAddrIpIdleTimeout,
		ltmTransAddrArpEnabled,
		ltmTransAddrUnitId,
		ltmTransAddrName
	}
	STATUS	 current
	DESCRIPTION
		"A collection of objects of ltmTransAddr MIB."
	::= { bigipLocalTMGroups 45 }

ltmTransAddrStatGroup OBJECT-GROUP
	 OBJECTS {
		ltmTransAddrStatResetStats,
		ltmTransAddrStatNumber,
		ltmTransAddrStatAddrType,
		ltmTransAddrStatAddr,
		ltmTransAddrStatServerPktsIn,
		ltmTransAddrStatServerBytesIn,
		ltmTransAddrStatServerPktsOut,
		ltmTransAddrStatServerBytesOut,
		ltmTransAddrStatServerMaxConns,
		ltmTransAddrStatServerTotConns,
		ltmTransAddrStatServerCurConns,
		ltmTransAddrStatName
	}
	STATUS	 current
	DESCRIPTION
		"A collection of objects of ltmTransAddrStat MIB."
	::= { bigipLocalTMGroups 46 }

ltmSnatPoolGroup OBJECT-GROUP
	 OBJECTS {
		ltmSnatPoolNumber,
		ltmSnatPoolName
	}
	STATUS	 current
	DESCRIPTION
		"A collection of objects of ltmSnatPool MIB."
	::= { bigipLocalTMGroups 47 }

ltmSnatPoolStatGroup OBJECT-GROUP
	 OBJECTS {
		ltmSnatPoolStatResetStats,
		ltmSnatPoolStatNumber,
		ltmSnatPoolStatName,
		ltmSnatPoolStatServerPktsIn,
		ltmSnatPoolStatServerBytesIn,
		ltmSnatPoolStatServerPktsOut,
		ltmSnatPoolStatServerBytesOut,
		ltmSnatPoolStatServerMaxConns,
		ltmSnatPoolStatServerTotConns,
		ltmSnatPoolStatServerCurConns
	}
	STATUS	 current
	DESCRIPTION
		"A collection of objects of ltmSnatPoolStat MIB."
	::= { bigipLocalTMGroups 48 }

ltmSnatpoolTransAddrGroup OBJECT-GROUP
	 OBJECTS {
		ltmSnatpoolTransAddrNumber,
		ltmSnatpoolTransAddrSnatpoolName,
		ltmSnatpoolTransAddrTransAddrType,
		ltmSnatpoolTransAddrTransAddr,
		ltmSnatpoolTransAddrTransAddrName
	}
	STATUS	 current
	DESCRIPTION
		"A collection of objects of ltmSnatpoolTransAddr MIB."
	::= { bigipLocalTMGroups 49 }

ltmVirtualServGroup OBJECT-GROUP
	 OBJECTS {
		ltmVirtualServNumber,
		ltmVirtualServName,
		ltmVirtualServAddrType,
		ltmVirtualServAddr,
		ltmVirtualServWildmaskType,
		ltmVirtualServWildmask,
		ltmVirtualServPort,
		ltmVirtualServIpProto,
		ltmVirtualServListedEnabledVlans,
		ltmVirtualServEnabled,
		ltmVirtualServConnLimit,
		ltmVirtualServRclass,
		ltmVirtualServSfFlags,
		ltmVirtualServTranslateAddr,
		ltmVirtualServTranslatePort,
		ltmVirtualServType,
		ltmVirtualServSnatType,
		ltmVirtualServLasthopPoolName,
		ltmVirtualServSnatpoolName,
		ltmVirtualServDefaultPool,
		ltmVirtualServFallbackPersist,
		ltmVirtualServActualPvaAccel,
		ltmVirtualServAvailabilityState,
		ltmVirtualServEnabledState,
		ltmVirtualServDisabledParentType,
		ltmVirtualServStatusReason,
		ltmVirtualServGtmScore,
		ltmVirtualServCmpEnabled,
		ltmVirtualServSrcport,
		ltmVirtualServVaName,
		ltmVirtualServSourceAddressTranslationType,
		ltmVirtualServSourceAddressTranslationPool,
		ltmVirtualServServiceDownImmediateAction,
		ltmVirtualServServersslUseSni
	}
	STATUS	 current
	DESCRIPTION
		"A collection of objects of ltmVirtualServ MIB."
	::= { bigipLocalTMGroups 50 }

ltmVirtualServStatGroup OBJECT-GROUP
	 OBJECTS {
		ltmVirtualServStatResetStats,
		ltmVirtualServStatNumber,
		ltmVirtualServStatName,
		ltmVirtualServStatCsMinConnDur,
		ltmVirtualServStatCsMaxConnDur,
		ltmVirtualServStatCsMeanConnDur,
		ltmVirtualServStatNoNodesErrors,
		ltmVirtualServStatClientPktsIn,
		ltmVirtualServStatClientBytesIn,
		ltmVirtualServStatClientPktsOut,
		ltmVirtualServStatClientBytesOut,
		ltmVirtualServStatClientMaxConns,
		ltmVirtualServStatClientTotConns,
		ltmVirtualServStatClientCurConns,
		ltmVirtualServStatEphemeralPktsIn,
		ltmVirtualServStatEphemeralBytesIn,
		ltmVirtualServStatEphemeralPktsOut,
		ltmVirtualServStatEphemeralBytesOut,
		ltmVirtualServStatEphemeralMaxConns,
		ltmVirtualServStatEphemeralTotConns,
		ltmVirtualServStatEphemeralCurConns,
		ltmVirtualServStatPvaPktsIn,
		ltmVirtualServStatPvaBytesIn,
		ltmVirtualServStatPvaPktsOut,
		ltmVirtualServStatPvaBytesOut,
		ltmVirtualServStatPvaMaxConns,
		ltmVirtualServStatPvaTotConns,
		ltmVirtualServStatPvaCurConns,
		ltmVirtualServStatTotRequests,
		ltmVirtualServStatTotPvaAssistConn,
		ltmVirtualServStatCurrPvaAssistConn,
		ltmVirtualServStatCycleCount,
		ltmVirtualServStatVsUsageRatio5s,
		ltmVirtualServStatVsUsageRatio1m,
		ltmVirtualServStatVsUsageRatio5m,
		ltmVirtualServStatCurrentConnsPerSec,
		ltmVirtualServStatDurationRateExceeded,
		ltmVirtualServStatSwSyncookies,
		ltmVirtualServStatSwSyncookieAccepts,
		ltmVirtualServStatHwSyncookies,
		ltmVirtualServStatHwSyncookieAccepts,
		ltmVirtualServStatClientEvictedConns,
		ltmVirtualServStatClientSlowKilled,
		ltmVirtualServStatWlSyncookieHits,
		ltmVirtualServStatWlSyncookieAccepts,
		ltmVirtualServStatWlSyncookieRejects,
		ltmVirtualServStatMsgMrIn,
		ltmVirtualServStatMsgMrOut,
		ltmVirtualServStatReqMrIn,
		ltmVirtualServStatReqMrOut,
		ltmVirtualServStatRespMrIn,
		ltmVirtualServStatRespMrOut
	}
	STATUS	 current
	DESCRIPTION
		"A collection of objects of ltmVirtualServStat MIB."
	::= { bigipLocalTMGroups 51 }

ltmVirtualServAuthGroup OBJECT-GROUP
	 OBJECTS {
		ltmVirtualServAuthNumber,
		ltmVirtualServAuthVsName,
		ltmVirtualServAuthProfileName
	}
	STATUS	 current
	DESCRIPTION
		"A collection of objects of ltmVirtualServAuth MIB."
	::= { bigipLocalTMGroups 52 }

ltmVirtualServPersistGroup OBJECT-GROUP
	 OBJECTS {
		ltmVirtualServPersistNumber,
		ltmVirtualServPersistVsName,
		ltmVirtualServPersistProfileName,
		ltmVirtualServPersistUseDefault
	}
	STATUS	 current
	DESCRIPTION
		"A collection of objects of ltmVirtualServPersist MIB."
	::= { bigipLocalTMGroups 53 }

ltmVirtualServProfileGroup OBJECT-GROUP
	 OBJECTS {
		ltmVirtualServProfileNumber,
		ltmVirtualServProfileVsName,
		ltmVirtualServProfileProfileName,
		ltmVirtualServProfileType,
		ltmVirtualServProfileContext
	}
	STATUS	 current
	DESCRIPTION
		"A collection of objects of ltmVirtualServProfile MIB."
	::= { bigipLocalTMGroups 54 }

ltmVirtualServPoolGroup OBJECT-GROUP
	 OBJECTS {
		ltmVirtualServPoolNumber,
		ltmVirtualServPoolVirtualServerName,
		ltmVirtualServPoolPoolName,
		ltmVirtualServPoolRuleName
	}
	STATUS	 current
	DESCRIPTION
		"A collection of objects of ltmVirtualServPool MIB."
	::= { bigipLocalTMGroups 55 }

ltmVirtualServClonePoolGroup OBJECT-GROUP
	 OBJECTS {
		ltmVirtualServClonePoolNumber,
		ltmVirtualServClonePoolVirtualServerName,
		ltmVirtualServClonePoolPoolName,
		ltmVirtualServClonePoolType
	}
	STATUS	 current
	DESCRIPTION
		"A collection of objects of ltmVirtualServClonePool MIB."
	::= { bigipLocalTMGroups 56 }

ltmVirtualServRuleGroup OBJECT-GROUP
	 OBJECTS {
		ltmVirtualServRuleNumber,
		ltmVirtualServRuleVirtualServerName,
		ltmVirtualServRuleRuleName,
		ltmVirtualServRulePriority
	}
	STATUS	 current
	DESCRIPTION
		"A collection of objects of ltmVirtualServRule MIB."
	::= { bigipLocalTMGroups 57 }

ltmVirtualServVlanGroup OBJECT-GROUP
	 OBJECTS {
		ltmVirtualServVlanNumber,
		ltmVirtualServVlanVsName,
		ltmVirtualServVlanVlanName
	}
	STATUS	 current
	DESCRIPTION
		"A collection of objects of ltmVirtualServVlan MIB."
	::= { bigipLocalTMGroups 58 }

ltmVirtualAddrGroup OBJECT-GROUP
	 OBJECTS {
		ltmVirtualAddrNumber,
		ltmVirtualAddrAddrType,
		ltmVirtualAddrAddr,
		ltmVirtualAddrEnabled,
		ltmVirtualAddrConnLimit,
		ltmVirtualAddrArpEnabled,
		ltmVirtualAddrSfFlags,
		ltmVirtualAddrUnitId,
		ltmVirtualAddrRouteAdvertisement,
		ltmVirtualAddrAvailabilityState,
		ltmVirtualAddrEnabledState,
		ltmVirtualAddrDisabledParentType,
		ltmVirtualAddrStatusReason,
		ltmVirtualAddrServer,
		ltmVirtualAddrIsFloat,
		ltmVirtualAddrName,
		ltmVirtualAddrIcmpEcho
	}
	STATUS	 current
	DESCRIPTION
		"A collection of objects of ltmVirtualAddr MIB."
	::= { bigipLocalTMGroups 59 }

ltmVirtualAddrStatGroup OBJECT-GROUP
	 OBJECTS {
		ltmVirtualAddrStatResetStats,
		ltmVirtualAddrStatNumber,
		ltmVirtualAddrStatAddrType,
		ltmVirtualAddrStatAddr,
		ltmVirtualAddrStatClientPktsIn,
		ltmVirtualAddrStatClientBytesIn,
		ltmVirtualAddrStatClientPktsOut,
		ltmVirtualAddrStatClientBytesOut,
		ltmVirtualAddrStatClientMaxConns,
		ltmVirtualAddrStatClientTotConns,
		ltmVirtualAddrStatClientCurConns,
		ltmVirtualAddrStatPvaPktsIn,
		ltmVirtualAddrStatPvaBytesIn,
		ltmVirtualAddrStatPvaPktsOut,
		ltmVirtualAddrStatPvaBytesOut,
		ltmVirtualAddrStatPvaMaxConns,
		ltmVirtualAddrStatPvaTotConns,
		ltmVirtualAddrStatPvaCurConns,
		ltmVirtualAddrStatTotPvaAssistConn,
		ltmVirtualAddrStatCurrPvaAssistConn,
		ltmVirtualAddrStatName
	}
	STATUS	 current
	DESCRIPTION
		"A collection of objects of ltmVirtualAddrStat MIB."
	::= { bigipLocalTMGroups 60 }

ltmFastHttpProfileGroup OBJECT-GROUP
	 OBJECTS {
		ltmFastHttpProfileNumber,
		ltmFastHttpProfileName,
		ltmFastHttpProfileConfigSource,
		ltmFastHttpProfileDefaultName,
		ltmFastHttpProfileResetOnTimeout,
		ltmFastHttpProfileIdleTimeout,
		ltmFastHttpProfileMssOverride,
		ltmFastHttpProfileClientCloseTimeout,
		ltmFastHttpProfileServerCloseTimeout,
		ltmFastHttpProfileConnpoolMaxSize,
		ltmFastHttpProfileConnpoolMinSize,
		ltmFastHttpProfileConnpoolStep,
		ltmFastHttpProfileConnpoolMaxReuse,
		ltmFastHttpProfileConnpoolIdleTimeout,
		ltmFastHttpProfileMaxHeaderSize,
		ltmFastHttpProfileMaxRequests,
		ltmFastHttpProfileInsertXforwardedFor,
		ltmFastHttpProfileHttp11CloseWorkarounds,
		ltmFastHttpProfileHeaderInsert,
		ltmFastHttpProfileUncleanShutdown,
		ltmFastHttpProfileForceHttp10Response,
		ltmFastHttpProfileLayer7,
		ltmFastHttpProfileConnpoolReplenish
	}
	STATUS	 current
	DESCRIPTION
		"A collection of objects of ltmFastHttpProfile MIB."
	::= { bigipLocalTMGroups 61 }

ltmFastHttpProfileStatGroup OBJECT-GROUP
	 OBJECTS {
		ltmFastHttpProfileStatResetStats,
		ltmFastHttpProfileStatNumber,
		ltmFastHttpProfileStatName,
		ltmFastHttpProfileStatClientSyns,
		ltmFastHttpProfileStatClientAccepts,
		ltmFastHttpProfileStatServerConnects,
		ltmFastHttpProfileStatConnpoolCurSize,
		ltmFastHttpProfileStatConnpoolMaxSize,
		ltmFastHttpProfileStatConnpoolReuses,
		ltmFastHttpProfileStatConnpoolExhausted,
		ltmFastHttpProfileStatNumberReqs,
		ltmFastHttpProfileStatUnbufferedReqs,
		ltmFastHttpProfileStatGetReqs,
		ltmFastHttpProfileStatPostReqs,
		ltmFastHttpProfileStatV9Reqs,
		ltmFastHttpProfileStatV10Reqs,
		ltmFastHttpProfileStatV11Reqs,
		ltmFastHttpProfileStatResp2xxCnt,
		ltmFastHttpProfileStatResp3xxCnt,
		ltmFastHttpProfileStatResp4xxCnt,
		ltmFastHttpProfileStatResp5xxCnt,
		ltmFastHttpProfileStatReqParseErrors,
		ltmFastHttpProfileStatRespParseErrors,
		ltmFastHttpProfileStatClientRxBad,
		ltmFastHttpProfileStatServerRxBad,
		ltmFastHttpProfileStatPipelinedReqs
	}
	STATUS	 current
	DESCRIPTION
		"A collection of objects of ltmFastHttpProfileStat MIB."
	::= { bigipLocalTMGroups 62 }

ltmXmlProfileGroup OBJECT-GROUP
	 OBJECTS {
		ltmXmlProfileNumber,
		ltmXmlProfileName,
		ltmXmlProfileConfigSource,
		ltmXmlProfileDefaultName,
		ltmXmlProfileAbortOnError,
		ltmXmlProfileMaxBufferSize,
		ltmXmlProfileMultipleQueryMatches
	}
	STATUS	 current
	DESCRIPTION
		"A collection of objects of ltmXmlProfile MIB."
	::= { bigipLocalTMGroups 63 }

ltmXmlProfileStatGroup OBJECT-GROUP
	 OBJECTS {
		ltmXmlProfileStatResetStats,
		ltmXmlProfileStatNumber,
		ltmXmlProfileStatName,
		ltmXmlProfileStatNumErrors,
		ltmXmlProfileStatNumInspectedDocuments,
		ltmXmlProfileStatNumDocumentsWithOneMatch,
		ltmXmlProfileStatNumDocumentsWithTwoMatches,
		ltmXmlProfileStatNumDocumentsWithThreeMatches,
		ltmXmlProfileStatNumDocumentsWithNoMatches,
		ltmXmlProfileStatNumMalformedDocuments
	}
	STATUS	 current
	DESCRIPTION
		"A collection of objects of ltmXmlProfileStat MIB."
	::= { bigipLocalTMGroups 64 }

ltmRamUriExclGroup OBJECT-GROUP
	 OBJECTS {
		ltmRamUriExclNumber,
		ltmRamUriExclName,
		ltmRamUriExclIndex,
		ltmRamUriExclUri
	}
	STATUS	 current
	DESCRIPTION
		"A collection of objects of ltmHttpProfileRamUriExcl MIB."
	::= { bigipLocalTMGroups 65 }

ltmRamUriInclGroup OBJECT-GROUP
	 OBJECTS {
		ltmRamUriInclNumber,
		ltmRamUriInclName,
		ltmRamUriInclIndex,
		ltmRamUriInclUri
	}
	STATUS	 current
	DESCRIPTION
		"A collection of objects of ltmHttpProfileRamUriIncl MIB."
	::= { bigipLocalTMGroups 66 }

ltmRamUriPinGroup OBJECT-GROUP
	 OBJECTS {
		ltmRamUriPinNumber,
		ltmRamUriPinName,
		ltmRamUriPinIndex,
		ltmRamUriPinUri
	}
	STATUS	 current
	DESCRIPTION
		"A collection of objects of ltmHttpProfileRamUriPin MIB."
	::= { bigipLocalTMGroups 67 }

ltmDnsProfileGroup OBJECT-GROUP
	 OBJECTS {
		ltmDnsProfileNumber,
		ltmDnsProfileName,
		ltmDnsProfileConfigSource,
		ltmDnsProfileDefaultName,
		ltmDnsProfileGtmEnabled,
		ltmDnsProfileDns64Mode,
		ltmDnsProfileDns64PrefixType,
		ltmDnsProfileDns64Prefix,
		ltmDnsProfileDns64AdditionalRewrite,
		ltmDnsProfileDnsLastAction,
		ltmDnsProfileUseLocalBind,
		ltmDnsProfileDnsExpressEnabled,
		ltmDnsProfileDnssecEnabled,
		ltmDnsProfileCacheEnabled,
		ltmDnsProfileDnsCache,
		ltmDnsProfileProcessRd,
		ltmDnsProfileAvrDnsStatSampleRate,
		ltmDnsProfileSecurity,
		ltmDnsProfileSecurityEnabled,
		ltmDnsProfileLoggingProfile,
		ltmDnsProfileLoggingEnabled,
		ltmDnsProfileFastDnsEnabled,
		ltmDnsProfileHwValidation,
		ltmDnsProfileHwCache
	}
	STATUS	 current
	DESCRIPTION
		"A collection of objects of ltmDnsProfile MIB."
	::= { bigipLocalTMGroups 68 }

ltmHttpClassGroup OBJECT-GROUP
	 OBJECTS {
		ltmHttpClassNumber,
		ltmHttpClassName,
		ltmHttpClassConfigSource,
		ltmHttpClassDefaultName,
		ltmHttpClassPoolName,
		ltmHttpClassAsmEnabled,
		ltmHttpClassWaEnabled,
		ltmHttpClassRedirectLocation,
		ltmHttpClassUrlRewrite
	}
	STATUS	 current
	DESCRIPTION
		"A collection of objects of ltmHttpClassProfile MIB."
	::= { bigipLocalTMGroups 69 }

ltmHttpClassHostGroup OBJECT-GROUP
	 OBJECTS {
		ltmHttpClassHostNumber,
		ltmHttpClassHostName,
		ltmHttpClassHostIndex,
		ltmHttpClassHostString
	}
	STATUS	 current
	DESCRIPTION
		"A collection of objects of ltmHttpClassProfileHost MIB."
	::= { bigipLocalTMGroups 70 }

ltmHttpClassUriGroup OBJECT-GROUP
	 OBJECTS {
		ltmHttpClassUriNumber,
		ltmHttpClassUriName,
		ltmHttpClassUriIndex,
		ltmHttpClassUriString
	}
	STATUS	 current
	DESCRIPTION
		"A collection of objects of ltmHttpClassProfileUri MIB."
	::= { bigipLocalTMGroups 71 }

ltmHttpClassHeadGroup OBJECT-GROUP
	 OBJECTS {
		ltmHttpClassHeadNumber,
		ltmHttpClassHeadName,
		ltmHttpClassHeadIndex,
		ltmHttpClassHeadString
	}
	STATUS	 current
	DESCRIPTION
		"A collection of objects of ltmHttpClassProfileHead MIB."
	::= { bigipLocalTMGroups 72 }

ltmHttpClassCookGroup OBJECT-GROUP
	 OBJECTS {
		ltmHttpClassCookNumber,
		ltmHttpClassCookName,
		ltmHttpClassCookIndex,
		ltmHttpClassCookString
	}
	STATUS	 current
	DESCRIPTION
		"A collection of objects of ltmHttpClassProfileCook MIB."
	::= { bigipLocalTMGroups 73 }

ltmHttpClassStatGroup OBJECT-GROUP
	 OBJECTS {
		ltmHttpClassStatResetStats,
		ltmHttpClassStatNumber,
		ltmHttpClassStatName,
		ltmHttpClassStatCookiePersistInserts,
		ltmHttpClassStatResp2xxCnt,
		ltmHttpClassStatResp3xxCnt,
		ltmHttpClassStatResp4xxCnt,
		ltmHttpClassStatResp5xxCnt,
		ltmHttpClassStatNumberReqs,
		ltmHttpClassStatGetReqs,
		ltmHttpClassStatPostReqs,
		ltmHttpClassStatV9Reqs,
		ltmHttpClassStatV10Reqs,
		ltmHttpClassStatV11Reqs,
		ltmHttpClassStatV9Resp,
		ltmHttpClassStatV10Resp,
		ltmHttpClassStatV11Resp,
		ltmHttpClassStatMaxKeepaliveReq,
		ltmHttpClassStatRespBucket1k,
		ltmHttpClassStatRespBucket4k,
		ltmHttpClassStatRespBucket16k,
		ltmHttpClassStatRespBucket32k,
		ltmHttpClassStatRespBucket64k,
		ltmHttpClassStatPrecompressBytes,
		ltmHttpClassStatPostcompressBytes,
		ltmHttpClassStatNullCompressBytes,
		ltmHttpClassStatHtmlPrecompressBytes,
		ltmHttpClassStatHtmlPostcompressBytes,
		ltmHttpClassStatCssPrecompressBytes,
		ltmHttpClassStatCssPostcompressBytes,
		ltmHttpClassStatJsPrecompressBytes,
		ltmHttpClassStatJsPostcompressBytes,
		ltmHttpClassStatXmlPrecompressBytes,
		ltmHttpClassStatXmlPostcompressBytes,
		ltmHttpClassStatSgmlPrecompressBytes,
		ltmHttpClassStatSgmlPostcompressBytes,
		ltmHttpClassStatPlainPrecompressBytes,
		ltmHttpClassStatPlainPostcompressBytes,
		ltmHttpClassStatOctetPrecompressBytes,
		ltmHttpClassStatOctetPostcompressBytes,
		ltmHttpClassStatImagePrecompressBytes,
		ltmHttpClassStatImagePostcompressBytes,
		ltmHttpClassStatVideoPrecompressBytes,
		ltmHttpClassStatVideoPostcompressBytes,
		ltmHttpClassStatAudioPrecompressBytes,
		ltmHttpClassStatAudioPostcompressBytes,
		ltmHttpClassStatOtherPrecompressBytes,
		ltmHttpClassStatOtherPostcompressBytes,
		ltmHttpClassStatRamcacheHits,
		ltmHttpClassStatRamcacheMisses,
		ltmHttpClassStatRamcacheMissesAll,
		ltmHttpClassStatRamcacheHitBytes,
		ltmHttpClassStatRamcacheMissBytes,
		ltmHttpClassStatRamcacheMissBytesAll
	}
	STATUS	 current
	DESCRIPTION
		"A collection of objects of ltmHttpClassProfileStat MIB."
	::= { bigipLocalTMGroups 74 }

ltmIiopProfileGroup OBJECT-GROUP
	 OBJECTS {
		ltmIiopProfileName,
		ltmIiopProfileConfigSource,
		ltmIiopProfileDefaultName,
		ltmIiopProfilePersistRequestId,
		ltmIiopProfilePersistObjectKey,
		ltmIiopProfileAbortOnTimeout,
		ltmIiopProfileTimeout
	}
	STATUS	 current
	DESCRIPTION
		"A collection of objects of ltmIiopProfile MIB."
	::= { bigipLocalTMGroups 75 }

ltmIiopProfileStatGroup OBJECT-GROUP
	 OBJECTS {
		ltmIiopProfileStatResetStats,
		ltmIiopProfileStatName,
		ltmIiopProfileStatNumRequests,
		ltmIiopProfileStatNumResponses,
		ltmIiopProfileStatNumCancels,
		ltmIiopProfileStatNumErrors,
		ltmIiopProfileStatNumFragments
	}
	STATUS	 current
	DESCRIPTION
		"A collection of objects of ltmIiopProfileStat MIB."
	::= { bigipLocalTMGroups 76 }

ltmRtspProfileGroup OBJECT-GROUP
	 OBJECTS {
		ltmRtspProfileNumber,
		ltmRtspProfileName,
		ltmRtspProfileConfigSource,
		ltmRtspProfileDefaultName,
		ltmRtspProfileIdleTimeout,
		ltmRtspProfileMaxHeaderSize,
		ltmRtspProfileMaxQueuedData,
		ltmRtspProfileUnicastRedirect,
		ltmRtspProfileMulticastRedirect,
		ltmRtspProfileSessionReconnect,
		ltmRtspProfileRealHttpPersistence,
		ltmRtspProfileProxy,
		ltmRtspProfileProxyHeader,
		ltmRtspProfileRtpPort,
		ltmRtspProfileRtcpPort,
		ltmRtspProfileLogPublisher,
		ltmRtspProfileLogProfile
	}
	STATUS	 current
	DESCRIPTION
		"A collection of objects of ltmRtspProfile MIB."
	::= { bigipLocalTMGroups 77 }

ltmRtspProfileStatGroup OBJECT-GROUP
	 OBJECTS {
		ltmRtspProfileStatResetStats,
		ltmRtspProfileStatNumber,
		ltmRtspProfileStatName,
		ltmRtspProfileStatNumRequests,
		ltmRtspProfileStatNumResponses,
		ltmRtspProfileStatNumErrors,
		ltmRtspProfileStatNumInterleaved
	}
	STATUS	 current
	DESCRIPTION
		"A collection of objects of ltmRtspProfileStat MIB."
	::= { bigipLocalTMGroups 78 }

ltmSctpProfileGroup OBJECT-GROUP
	 OBJECTS {
		ltmSctpProfileNumber,
		ltmSctpProfileName,
		ltmSctpProfileConfigSource,
		ltmSctpProfileDefaultName,
		ltmSctpProfileRcvOrdered,
		ltmSctpProfileSndPartial,
		ltmSctpProfileTcpShutdown,
		ltmSctpProfileResetOnTimeout,
		ltmSctpProfileOutStreams,
		ltmSctpProfileInStreams,
		ltmSctpProfileSndbuf,
		ltmSctpProfileRcvwnd,
		ltmSctpProfileTxChunks,
		ltmSctpProfileRxChunks,
		ltmSctpProfileCookieExpiration,
		ltmSctpProfileInitMaxrtx,
		ltmSctpProfileAssocMaxrtx,
		ltmSctpProfileProxyBufferLow,
		ltmSctpProfileProxyBufferHigh,
		ltmSctpProfileIdleTimeout,
		ltmSctpProfileHeartbeatInterval,
		ltmSctpProfileIpTosToPeer,
		ltmSctpProfileLinkQosToPeer,
		ltmSctpProfileSecret,
		ltmSctpProfileMaxBurst,
		ltmSctpProfileHeartbeatMaxBurst,
		ltmSctpProfileMaxCommunicationPaths,
		ltmSctpProfileMaxPathRetransmitLimit,
		ltmSctpProfileServerSideMultihoming,
		ltmSctpProfileClientSideMultihoming,
		ltmSctpProfileRtoInitial,
		ltmSctpProfileRtoMin,
		ltmSctpProfileRtoMax,
		ltmSctpProfileSackTimeout
	}
	STATUS	 current
	DESCRIPTION
		"A collection of objects of ltmSctpProfile MIB."
	::= { bigipLocalTMGroups 79 }

ltmSctpProfileStatGroup OBJECT-GROUP
	 OBJECTS {
		ltmSctpProfileStatResetStats,
		ltmSctpProfileStatNumber,
		ltmSctpProfileStatName,
		ltmSctpProfileStatAccepts,
		ltmSctpProfileStatAcceptfails,
		ltmSctpProfileStatConnects,
		ltmSctpProfileStatConnfails,
		ltmSctpProfileStatExpires,
		ltmSctpProfileStatAbandons,
		ltmSctpProfileStatRxrst,
		ltmSctpProfileStatRxbadsum,
		ltmSctpProfileStatRxcookie,
		ltmSctpProfileStatRxbadcookie,
		ltmSctpProfileStatAssociations,
		ltmSctpProfileStatClosing,
		ltmSctpProfileStatConfirmedAddresses,
		ltmSctpProfileStatUnconfirmedAddresses,
		ltmSctpProfileStatActivePaths,
		ltmSctpProfileStatInactivePaths
	}
	STATUS	 current
	DESCRIPTION
		"A collection of objects of ltmSctpProfileStat MIB."
	::= { bigipLocalTMGroups 80 }

ltmUserStatProfileGroup OBJECT-GROUP
	 OBJECTS {
		ltmUserStatProfileNumber,
		ltmUserStatProfileName,
		ltmUserStatProfileConfigSource,
		ltmUserStatProfileDefaultName
	}
	STATUS	 current
	DESCRIPTION
		"A collection of objects of ltmUserStatProfile MIB."
	::= { bigipLocalTMGroups 81 }

ltmUserStatProfileStatGroup OBJECT-GROUP
	 OBJECTS {
		ltmUserStatProfileStatResetStats,
		ltmUserStatProfileStatNumber,
		ltmUserStatProfileStatName,
		ltmUserStatProfileStatFieldId,
		ltmUserStatProfileStatFieldName,
		ltmUserStatProfileStatFieldValue
	}
	STATUS	 current
	DESCRIPTION
		"A collection of objects of ltmUserStatProfileStat MIB."
	::= { bigipLocalTMGroups 83 }

ltmVsHttpClassGroup OBJECT-GROUP
	 OBJECTS {
		ltmVsHttpClassNumber,
		ltmVsHttpClassVsName,
		ltmVsHttpClassProfileName,
		ltmVsHttpClassPriority
	}
	STATUS	 current
	DESCRIPTION
		"A collection of objects of ltmVirtualServHttpClass MIB."
	::= { bigipLocalTMGroups 84 }

ltmNodeAddrStatusGroup OBJECT-GROUP
	 OBJECTS {
		ltmNodeAddrStatusNumber,
		ltmNodeAddrStatusAddrType,
		ltmNodeAddrStatusAddr,
		ltmNodeAddrStatusAvailState,
		ltmNodeAddrStatusEnabledState,
		ltmNodeAddrStatusParentType,
		ltmNodeAddrStatusDetailReason,
		ltmNodeAddrStatusName
	}
	STATUS	 current
	DESCRIPTION
		"A collection of objects of ltmNodeAddrStatus MIB."
	::= { bigipLocalTMGroups 85 }

ltmPoolStatusGroup OBJECT-GROUP
	 OBJECTS {
		ltmPoolStatusNumber,
		ltmPoolStatusName,
		ltmPoolStatusAvailState,
		ltmPoolStatusEnabledState,
		ltmPoolStatusParentType,
		ltmPoolStatusDetailReason
	}
	STATUS	 current
	DESCRIPTION
		"A collection of objects of ltmPoolStatus MIB."
	::= { bigipLocalTMGroups 86 }

ltmPoolMbrStatusGroup OBJECT-GROUP
	 OBJECTS {
		ltmPoolMbrStatusNumber,
		ltmPoolMbrStatusPoolName,
		ltmPoolMbrStatusAddrType,
		ltmPoolMbrStatusAddr,
		ltmPoolMbrStatusPort,
		ltmPoolMbrStatusAvailState,
		ltmPoolMbrStatusEnabledState,
		ltmPoolMbrStatusParentType,
		ltmPoolMbrStatusDetailReason,
		ltmPoolMbrStatusNodeName
	}
	STATUS	 current
	DESCRIPTION
		"A collection of objects of ltmPoolMemberStatus MIB."
	::= { bigipLocalTMGroups 87 }

ltmVsStatusGroup OBJECT-GROUP
	 OBJECTS {
		ltmVsStatusNumber,
		ltmVsStatusName,
		ltmVsStatusAvailState,
		ltmVsStatusEnabledState,
		ltmVsStatusParentType,
		ltmVsStatusDetailReason
	}
	STATUS	 current
	DESCRIPTION
		"A collection of objects of ltmVirtualServStatus MIB."
	::= { bigipLocalTMGroups 88 }

ltmVAddrStatusGroup OBJECT-GROUP
	 OBJECTS {
		ltmVAddrStatusNumber,
		ltmVAddrStatusAddrType,
		ltmVAddrStatusAddr,
		ltmVAddrStatusAvailState,
		ltmVAddrStatusEnabledState,
		ltmVAddrStatusParentType,
		ltmVAddrStatusDetailReason,
		ltmVAddrStatusName
	}
	STATUS	 current
	DESCRIPTION
		"A collection of objects of ltmVirtualAddrStatus MIB."
	::= { bigipLocalTMGroups 89 }

ltmFallbackStatusGroup OBJECT-GROUP
	 OBJECTS {
		ltmFallbackStatusNumber,
		ltmFallbackStatusName,
		ltmFallbackStatusIndex,
		ltmFallbackStatusCode
	}
	STATUS	 current
	DESCRIPTION
		"A collection of objects of ltmHttpProfileFallbackStatus MIB."
	::= { bigipLocalTMGroups 90 }

ltmRespHeadersPermGroup OBJECT-GROUP
	 OBJECTS {
		ltmRespHeadersPermNumber,
		ltmRespHeadersPermName,
		ltmRespHeadersPermIndex,
		ltmRespHeadersPermStr
	}
	STATUS	 current
	DESCRIPTION
		"A collection of objects of ltmHttpProfileRespHeadersPerm MIB."
	::= { bigipLocalTMGroups 91 }

ltmEncCookiesGroup OBJECT-GROUP
	 OBJECTS {
		ltmEncCookiesNumber,
		ltmEncCookiesName,
		ltmEncCookiesIndex,
		ltmEncCookiesStr
	}
	STATUS	 current
	DESCRIPTION
		"A collection of objects of ltmHttpProfileEncCookies MIB."
	::= { bigipLocalTMGroups 92 }

ltmFastL4ProfileStatGroup OBJECT-GROUP
	 OBJECTS {
		ltmFastL4ProfileStatResetStats,
		ltmFastL4ProfileStatNumber,
		ltmFastL4ProfileStatName,
		ltmFastL4ProfileStatOpen,
		ltmFastL4ProfileStatAccepts,
		ltmFastL4ProfileStatAcceptfails,
		ltmFastL4ProfileStatExpires,
		ltmFastL4ProfileStatRxbadpkt,
		ltmFastL4ProfileStatRxunreach,
		ltmFastL4ProfileStatRxbadunreach,
		ltmFastL4ProfileStatRxbadsum,
		ltmFastL4ProfileStatTxerrors,
		ltmFastL4ProfileStatSyncookIssue,
		ltmFastL4ProfileStatSyncookAccept,
		ltmFastL4ProfileStatSyncookReject,
		ltmFastL4ProfileStatServersynrtx,
		ltmFastL4ProfileStatLbcSuccessful,
		ltmFastL4ProfileStatLbcTimedout
	}
	STATUS	 current
	DESCRIPTION
		"A collection of objects of ltmFastL4ProfileStat MIB."
	::= { bigipLocalTMGroups 93 }

ltmSipProfileGroup OBJECT-GROUP
	 OBJECTS {
		ltmSipProfileNumber,
		ltmSipProfileName,
		ltmSipProfileConfigSource,
		ltmSipProfileDefaultName,
		ltmSipProfileMaxSize,
		ltmSipProfileTerminateBye,
		ltmSipProfileInsertVia,
		ltmSipProfileSecureVia,
		ltmSipProfileInsertRecordRoute,
		ltmSipProfileFirewallEnabled,
		ltmSipProfileLogPublisher,
		ltmSipProfileLogProfile
	}
	STATUS	 current
	DESCRIPTION
		"A collection of objects of ltmSipProfile MIB."
	::= { bigipLocalTMGroups 94 }

ltmSipProfileStatGroup OBJECT-GROUP
	 OBJECTS {
		ltmSipProfileStatResetStats,
		ltmSipProfileStatNumber,
		ltmSipProfileStatName,
		ltmSipProfileStatRequests,
		ltmSipProfileStatResponses,
		ltmSipProfileStatBadmsgs,
		ltmSipProfileStatDrops
	}
	STATUS	 current
	DESCRIPTION
		"A collection of objects of ltmSipProfileStat MIB."
	::= { bigipLocalTMGroups 95 }

ltmVirtualModuleScoreGroup OBJECT-GROUP
	 OBJECTS {
		ltmVirtualModuleScoreNumber,
		ltmVirtualModuleScoreVsName,
		ltmVirtualModuleScoreModuleType,
		ltmVirtualModuleScoreScore
	}
	STATUS	 current
	DESCRIPTION
		"A collection of objects of ltmVirtualModuleScore MIB."
	::= { bigipLocalTMGroups 96 }

ltmIsessionProfileGroup OBJECT-GROUP
	 OBJECTS {
		ltmIsessionProfileNumber,
		ltmIsessionProfileName,
		ltmIsessionProfileMode,
		ltmIsessionProfileConnectionReuse,
		ltmIsessionProfileCompressionNull,
		ltmIsessionProfileCompressionDeflate,
		ltmIsessionProfileCompressionLzo,
		ltmIsessionProfileCompressionAdaptive,
		ltmIsessionProfileDeduplication,
		ltmIsessionProfilePortTransparency,
		ltmIsessionProfileTargetVirtual,
		ltmIsessionProfileEndpointPool,
		ltmIsessionProfileCompressionDeflateLevel,
		ltmIsessionProfileCompressionBzip2,
		ltmIsessionProfileCompression,
		ltmIsessionProfileCompressionCodecs
	}
	STATUS	 current
	DESCRIPTION
		"A collection of objects of ltmIsessionProfile MIB."
	::= { bigipLocalTMGroups 97 }

ltmIsessionProfileStatGroup OBJECT-GROUP
	 OBJECTS {
		ltmIsessionProfileStatResetStats,
		ltmIsessionProfileStatNumber,
		ltmIsessionProfileStatVsName,
		ltmIsessionProfileStatProfileName,
		ltmIsessionProfileStatNullInUses,
		ltmIsessionProfileStatNullInErrors,
		ltmIsessionProfileStatNullInBytesOpt,
		ltmIsessionProfileStatNullInBytesRaw,
		ltmIsessionProfileStatNullOutUses,
		ltmIsessionProfileStatNullOutErrors,
		ltmIsessionProfileStatNullOutBytesOpt,
		ltmIsessionProfileStatNullOutBytesRaw,
		ltmIsessionProfileStatLzoInUses,
		ltmIsessionProfileStatLzoInErrors,
		ltmIsessionProfileStatLzoInBytesOpt,
		ltmIsessionProfileStatLzoInBytesRaw,
		ltmIsessionProfileStatLzoOutUses,
		ltmIsessionProfileStatLzoOutErrors,
		ltmIsessionProfileStatLzoOutBytesOpt,
		ltmIsessionProfileStatLzoOutBytesRaw,
		ltmIsessionProfileStatDeflateInUses,
		ltmIsessionProfileStatDeflateInErrors,
		ltmIsessionProfileStatDeflateInBytesOpt,
		ltmIsessionProfileStatDeflateInBytesRaw,
		ltmIsessionProfileStatDeflateOutUses,
		ltmIsessionProfileStatDeflateOutErrors,
		ltmIsessionProfileStatDeflateOutBytesOpt,
		ltmIsessionProfileStatDeflateOutBytesRaw,
		ltmIsessionProfileStatDedupInUses,
		ltmIsessionProfileStatDedupInErrors,
		ltmIsessionProfileStatDedupInBytesOpt,
		ltmIsessionProfileStatDedupInBytesRaw,
		ltmIsessionProfileStatDedupOutUses,
		ltmIsessionProfileStatDedupOutErrors,
		ltmIsessionProfileStatDedupOutBytesOpt,
		ltmIsessionProfileStatDedupOutBytesRaw,
		ltmIsessionProfileStatDedupInHits,
		ltmIsessionProfileStatDedupInHitBytes,
		ltmIsessionProfileStatDedupInHitHistBucket1k,
		ltmIsessionProfileStatDedupInHitHistBucket2k,
		ltmIsessionProfileStatDedupInHitHistBucket4k,
		ltmIsessionProfileStatDedupInHitHistBucket8k,
		ltmIsessionProfileStatDedupInHitHistBucket16k,
		ltmIsessionProfileStatDedupInHitHistBucket32k,
		ltmIsessionProfileStatDedupInHitHistBucket64k,
		ltmIsessionProfileStatDedupInHitHistBucket128k,
		ltmIsessionProfileStatDedupInHitHistBucket256k,
		ltmIsessionProfileStatDedupInHitHistBucket512k,
		ltmIsessionProfileStatDedupInHitHistBucket1m,
		ltmIsessionProfileStatDedupInHitHistBucketLarge,
		ltmIsessionProfileStatDedupInMisses,
		ltmIsessionProfileStatDedupInMissBytes,
		ltmIsessionProfileStatDedupInMissHistBucket1k,
		ltmIsessionProfileStatDedupInMissHistBucket2k,
		ltmIsessionProfileStatDedupInMissHistBucket4k,
		ltmIsessionProfileStatDedupInMissHistBucket8k,
		ltmIsessionProfileStatDedupInMissHistBucket16k,
		ltmIsessionProfileStatDedupInMissHistBucket32k,
		ltmIsessionProfileStatDedupInMissHistBucket64k,
		ltmIsessionProfileStatDedupInMissHistBucket128k,
		ltmIsessionProfileStatDedupInMissHistBucket256k,
		ltmIsessionProfileStatDedupInMissHistBucket512k,
		ltmIsessionProfileStatDedupInMissHistBucket1m,
		ltmIsessionProfileStatDedupInMissHistBucketLarge,
		ltmIsessionProfileStatDedupOutHits,
		ltmIsessionProfileStatDedupOutHitBytes,
		ltmIsessionProfileStatDedupOutHitHistBucket1k,
		ltmIsessionProfileStatDedupOutHitHistBucket2k,
		ltmIsessionProfileStatDedupOutHitHistBucket4k,
		ltmIsessionProfileStatDedupOutHitHistBucket8k,
		ltmIsessionProfileStatDedupOutHitHistBucket16k,
		ltmIsessionProfileStatDedupOutHitHistBucket32k,
		ltmIsessionProfileStatDedupOutHitHistBucket64k,
		ltmIsessionProfileStatDedupOutHitHistBucket128k,
		ltmIsessionProfileStatDedupOutHitHistBucket256k,
		ltmIsessionProfileStatDedupOutHitHistBucket512k,
		ltmIsessionProfileStatDedupOutHitHistBucket1m,
		ltmIsessionProfileStatDedupOutHitHistBucketLarge,
		ltmIsessionProfileStatDedupOutMisses,
		ltmIsessionProfileStatDedupOutMissBytes,
		ltmIsessionProfileStatDedupOutMissHistBucket1k,
		ltmIsessionProfileStatDedupOutMissHistBucket2k,
		ltmIsessionProfileStatDedupOutMissHistBucket4k,
		ltmIsessionProfileStatDedupOutMissHistBucket8k,
		ltmIsessionProfileStatDedupOutMissHistBucket16k,
		ltmIsessionProfileStatDedupOutMissHistBucket32k,
		ltmIsessionProfileStatDedupOutMissHistBucket64k,
		ltmIsessionProfileStatDedupOutMissHistBucket128k,
		ltmIsessionProfileStatDedupOutMissHistBucket256k,
		ltmIsessionProfileStatDedupOutMissHistBucket512k,
		ltmIsessionProfileStatDedupOutMissHistBucket1m,
		ltmIsessionProfileStatDedupOutMissHistBucketLarge,
		ltmIsessionProfileStatOutgoingConnsIdleCur,
		ltmIsessionProfileStatOutgoingConnsIdleMax,
		ltmIsessionProfileStatOutgoingConnsIdleTot,
		ltmIsessionProfileStatOutgoingConnsActiveCur,
		ltmIsessionProfileStatOutgoingConnsActiveMax,
		ltmIsessionProfileStatOutgoingConnsActiveTot,
		ltmIsessionProfileStatOutgoingConnsErrors,
		ltmIsessionProfileStatOutgoingConnsPassthruTot,
		ltmIsessionProfileStatIncomingConnsActiveCur,
		ltmIsessionProfileStatIncomingConnsActiveMax,
		ltmIsessionProfileStatIncomingConnsActiveTot,
		ltmIsessionProfileStatIncomingConnsErrors,
		ltmIsessionProfileStatBzip2InUses,
		ltmIsessionProfileStatBzip2InErrors,
		ltmIsessionProfileStatBzip2InBytesOpt,
		ltmIsessionProfileStatBzip2InBytesRaw,
		ltmIsessionProfileStatBzip2OutUses,
		ltmIsessionProfileStatBzip2OutErrors,
		ltmIsessionProfileStatBzip2OutBytesOpt,
		ltmIsessionProfileStatBzip2OutBytesRaw
	}
	STATUS	 current
	DESCRIPTION
		"A collection of objects of ltmIsessionProfileStat MIB."
	::= { bigipLocalTMGroups 98 }

ltmXmlProfileXpathQueriesGroup OBJECT-GROUP
	 OBJECTS {
		ltmXmlProfileXpathQueriesNumber,
		ltmXmlProfileXpathQueriesName,
		ltmXmlProfileXpathQueriesIndex,
		ltmXmlProfileXpathQueriesString
	}
	STATUS	 current
	DESCRIPTION
		"A collection of objects of ltmXmlProfileXpathQueries MIB."
	::= { bigipLocalTMGroups 99 }

ltmXmlProfileNamespaceMappingsGroup OBJECT-GROUP
	 OBJECTS {
		ltmXmlProfileNamespaceMappingsNumber,
		ltmXmlProfileNamespaceMappingsName,
		ltmXmlProfileNamespaceMappingsIndex,
		ltmXmlProfileNamespaceMappingsMappingPrefix,
		ltmXmlProfileNamespaceMappingsMappingNamespace
	}
	STATUS	 current
	DESCRIPTION
		"A collection of objects of ltmXmlProfileNamespaceMappings MIB."
	::= { bigipLocalTMGroups 100 }

ltmHttpCompressionProfileGroup OBJECT-GROUP
	 OBJECTS {
		ltmHttpCompressionProfileNumber,
		ltmHttpCompressionProfileName,
		ltmHttpCompressionProfileConfigSource,
		ltmHttpCompressionProfileDefaultName,
		ltmHttpCompressionProfileSelective,
		ltmHttpCompressionProfileMinSize,
		ltmHttpCompressionProfileBufferSize,
		ltmHttpCompressionProfileVaryHeader,
		ltmHttpCompressionProfileAllowHttp10,
		ltmHttpCompressionProfileGzipMemlevel,
		ltmHttpCompressionProfileGzipWindowsize,
		ltmHttpCompressionProfileGzipLevel,
		ltmHttpCompressionProfileKeepAcceptEncoding,
		ltmHttpCompressionProfileBrowserWorkarounds,
		ltmHttpCompressionProfileCpusaver,
		ltmHttpCompressionProfileCpusaverHigh,
		ltmHttpCompressionProfileCpusaverLow,
		ltmHttpCompressionProfilePreferredMethod
	}
	STATUS	 current
	DESCRIPTION
		"A collection of objects of ltmHttpCompressionProfile MIB."
	::= { bigipLocalTMGroups 101 }

ltmHttpcompUriInclGroup OBJECT-GROUP
	 OBJECTS {
		ltmHttpcompUriInclNumber,
		ltmHttpcompUriInclName,
		ltmHttpcompUriInclIndex,
		ltmHttpcompUriInclUri
	}
	STATUS	 current
	DESCRIPTION
		"A collection of objects of ltmHttpCompressionProfileUriIncl MIB."
	::= { bigipLocalTMGroups 102 }

ltmHttpcompUriExclGroup OBJECT-GROUP
	 OBJECTS {
		ltmHttpcompUriExclNumber,
		ltmHttpcompUriExclName,
		ltmHttpcompUriExclIndex,
		ltmHttpcompUriExclUri
	}
	STATUS	 current
	DESCRIPTION
		"A collection of objects of ltmHttpCompressionProfileUriExcl MIB."
	::= { bigipLocalTMGroups 103 }

ltmHttpcompContTypeInclGroup OBJECT-GROUP
	 OBJECTS {
		ltmHttpcompContTypeInclNumber,
		ltmHttpcompContTypeInclName,
		ltmHttpcompContTypeInclIndex,
		ltmHttpcompContTypeInclContentType
	}
	STATUS	 current
	DESCRIPTION
		"A collection of objects of ltmHttpCompressionProfileContTypeIncl MIB."
	::= { bigipLocalTMGroups 104 }

ltmHttpcompContTypeExclGroup OBJECT-GROUP
	 OBJECTS {
		ltmHttpcompContTypeExclNumber,
		ltmHttpcompContTypeExclName,
		ltmHttpcompContTypeExclIndex,
		ltmHttpcompContTypeExclContentType
	}
	STATUS	 current
	DESCRIPTION
		"A collection of objects of ltmHttpCompressionProfileContTypeExcl MIB."
	::= { bigipLocalTMGroups 105 }

ltmHttpCompressionProfileStatGroup OBJECT-GROUP
	 OBJECTS {
		ltmHttpCompressionProfileStatResetStats,
		ltmHttpCompressionProfileStatNumber,
		ltmHttpCompressionProfileStatName,
		ltmHttpCompressionProfileStatPrecompressBytes,
		ltmHttpCompressionProfileStatPostcompressBytes,
		ltmHttpCompressionProfileStatNullCompressBytes,
		ltmHttpCompressionProfileStatHtmlPrecompressBytes,
		ltmHttpCompressionProfileStatHtmlPostcompressBytes,
		ltmHttpCompressionProfileStatCssPrecompressBytes,
		ltmHttpCompressionProfileStatCssPostcompressBytes,
		ltmHttpCompressionProfileStatJsPrecompressBytes,
		ltmHttpCompressionProfileStatJsPostcompressBytes,
		ltmHttpCompressionProfileStatXmlPrecompressBytes,
		ltmHttpCompressionProfileStatXmlPostcompressBytes,
		ltmHttpCompressionProfileStatSgmlPrecompressBytes,
		ltmHttpCompressionProfileStatSgmlPostcompressBytes,
		ltmHttpCompressionProfileStatPlainPrecompressBytes,
		ltmHttpCompressionProfileStatPlainPostcompressBytes,
		ltmHttpCompressionProfileStatOctetPrecompressBytes,
		ltmHttpCompressionProfileStatOctetPostcompressBytes,
		ltmHttpCompressionProfileStatImagePrecompressBytes,
		ltmHttpCompressionProfileStatImagePostcompressBytes,
		ltmHttpCompressionProfileStatVideoPrecompressBytes,
		ltmHttpCompressionProfileStatVideoPostcompressBytes,
		ltmHttpCompressionProfileStatAudioPrecompressBytes,
		ltmHttpCompressionProfileStatAudioPostcompressBytes,
		ltmHttpCompressionProfileStatOtherPrecompressBytes,
		ltmHttpCompressionProfileStatOtherPostcompressBytes
	}
	STATUS	 current
	DESCRIPTION
		"A collection of objects of ltmHttpCompressionProfileStat MIB."
	::= { bigipLocalTMGroups 106 }

ltmWebAccelerationProfileGroup OBJECT-GROUP
	 OBJECTS {
		ltmWebAccelerationProfileNumber,
		ltmWebAccelerationProfileName,
		ltmWebAccelerationProfileConfigSource,
		ltmWebAccelerationProfileDefaultName,
		ltmWebAccelerationProfileCacheSize,
		ltmWebAccelerationProfileCacheMaxEntries,
		ltmWebAccelerationProfileCacheMaxAge,
		ltmWebAccelerationProfileCacheObjectMinSize,
		ltmWebAccelerationProfileCacheObjectMaxSize,
		ltmWebAccelerationProfileCacheIgnoreClient,
		ltmWebAccelerationProfileCacheAgingRate,
		ltmWebAccelerationProfileCacheInsertAgeHeader
	}
	STATUS	 current
	DESCRIPTION
		"A collection of objects of ltmWebAccelerationProfile MIB."
	::= { bigipLocalTMGroups 107 }

ltmWebaccCacheUriExclGroup OBJECT-GROUP
	 OBJECTS {
		ltmWebaccCacheUriExclNumber,
		ltmWebaccCacheUriExclName,
		ltmWebaccCacheUriExclIndex,
		ltmWebaccCacheUriExclUri
	}
	STATUS	 current
	DESCRIPTION
		"A collection of objects of ltmWebAccelerationProfileUriExcl MIB."
	::= { bigipLocalTMGroups 108 }

ltmWebaccCacheUriInclGroup OBJECT-GROUP
	 OBJECTS {
		ltmWebaccCacheUriInclNumber,
		ltmWebaccCacheUriInclName,
		ltmWebaccCacheUriInclIndex,
		ltmWebaccCacheUriInclUri
	}
	STATUS	 current
	DESCRIPTION
		"A collection of objects of ltmWebAccelerationProfileUriIncl MIB."
	::= { bigipLocalTMGroups 109 }

ltmWebaccCacheUriPinGroup OBJECT-GROUP
	 OBJECTS {
		ltmWebaccCacheUriPinNumber,
		ltmWebaccCacheUriPinName,
		ltmWebaccCacheUriPinIndex,
		ltmWebaccCacheUriPinUri
	}
	STATUS	 current
	DESCRIPTION
		"A collection of objects of ltmWebAccelerationProfileUriPin MIB."
	::= { bigipLocalTMGroups 110 }

ltmWebAccelerationProfileStatGroup OBJECT-GROUP
	 OBJECTS {
		ltmWebAccelerationProfileStatResetStats,
		ltmWebAccelerationProfileStatNumber,
		ltmWebAccelerationProfileStatName,
		ltmWebAccelerationProfileStatCacheHits,
		ltmWebAccelerationProfileStatCacheMisses,
		ltmWebAccelerationProfileStatCacheMissesAll,
		ltmWebAccelerationProfileStatCacheHitBytes,
		ltmWebAccelerationProfileStatCacheMissBytes,
		ltmWebAccelerationProfileStatCacheMissBytesAll,
		ltmWebAccelerationProfileStatCacheSize,
		ltmWebAccelerationProfileStatCacheCount,
		ltmWebAccelerationProfileStatCacheEvictions,
		ltmWebAccelerationProfileStatInterStripeHits,
		ltmWebAccelerationProfileStatInterStripeMisses,
		ltmWebAccelerationProfileStatInterStripeHitBytes,
		ltmWebAccelerationProfileStatInterStripeSize,
		ltmWebAccelerationProfileStatInterStripeCount,
		ltmWebAccelerationProfileStatInterStripeEvictions,
		ltmWebAccelerationProfileStatRemoteHits,
		ltmWebAccelerationProfileStatRemoteMisses,
		ltmWebAccelerationProfileStatRemoteHitBytes
	}
	STATUS	 current
	DESCRIPTION
		"A collection of objects of ltmWebAccelerationProfileStat MIB."
	::= { bigipLocalTMGroups 111 }

ltmRstCauseStatGroup OBJECT-GROUP
	 OBJECTS {
		ltmRstCauseStatResetStats,
		ltmRstCauseStatNumber,
		ltmRstCauseStatIndex,
		ltmRstCauseStatRstCause,
		ltmRstCauseStatCount
	}
	STATUS	 current
	DESCRIPTION
		"A collection of objects of ltmRstCauseStat MIB."
	::= { bigipLocalTMGroups 112 }

ltmWebaccCacheUriOverGroup OBJECT-GROUP
	 OBJECTS {
		ltmWebaccCacheUriOverNumber,
		ltmWebaccCacheUriOverName,
		ltmWebaccCacheUriOverIndex,
		ltmWebaccCacheUriOverUri
	}
	STATUS	 current
	DESCRIPTION
		"A collection of objects of ltmWebAccelerationProfileUriOver MIB."
	::= { bigipLocalTMGroups 113 }

ltmDnsCacheGroup OBJECT-GROUP
	 OBJECTS {
		ltmDnsCacheNumber,
		ltmDnsCacheName,
		ltmDnsCacheType,
		ltmDnsCacheMsgCacheSize,
		ltmDnsCacheRrsetCacheSize,
		ltmDnsCacheAnswerDefaultZones,
		ltmDnsCacheUseIpv4,
		ltmDnsCacheUseIpv6,
		ltmDnsCacheUseUdp,
		ltmDnsCacheUseTcp,
		ltmDnsCacheNameserverCacheCount,
		ltmDnsCacheMaxConcurrentTcp,
		ltmDnsCacheMaxConcurrentUdp,
		ltmDnsCacheUnwantedThreshold,
		ltmDnsCacheRouteDomainName,
		ltmDnsCacheIgnoreCd,
		ltmDnsCachePrefetchKey,
		ltmDnsCacheKeyCacheSize,
		ltmDnsCacheRandomizeQueryNameCase,
		ltmDnsCacheMaxConcurrentQueries,
		ltmDnsCacheAllowedQueryTime
	}
	STATUS	 current
	DESCRIPTION
		"A collection of objects of ltmDnsCache MIB."
	::= { bigipLocalTMGroups 114 }

ltmDnsCacheStatGroup OBJECT-GROUP
	 OBJECTS {
		ltmDnsCacheStatResetStats,
		ltmDnsCacheStatNumber,
		ltmDnsCacheStatName,
		ltmDnsCacheStatQueries,
		ltmDnsCacheStatResponses,
		ltmDnsCacheStatSync,
		ltmDnsCacheStatAsync,
		ltmDnsCacheStatFailureResolv,
		ltmDnsCacheStatFailureCf,
		ltmDnsCacheStatFailureServer,
		ltmDnsCacheStatFailureSend,
		ltmDnsCacheStatMsgHits,
		ltmDnsCacheStatMsgMisses,
		ltmDnsCacheStatMsgInserts,
		ltmDnsCacheStatMsgUpdates,
		ltmDnsCacheStatMsgEvictions,
		ltmDnsCacheStatRrsetHits,
		ltmDnsCacheStatRrsetMisses,
		ltmDnsCacheStatRrsetInserts,
		ltmDnsCacheStatRrsetUpdates,
		ltmDnsCacheStatRrsetEvictions,
		ltmDnsCacheStatNameserverHits,
		ltmDnsCacheStatNameserverMisses,
		ltmDnsCacheStatNameserverInserts,
		ltmDnsCacheStatNameserverUpdates,
		ltmDnsCacheStatNameserverEvictions,
		ltmDnsCacheStatKeyHits,
		ltmDnsCacheStatKeyMisses,
		ltmDnsCacheStatKeyInserts,
		ltmDnsCacheStatKeyUpdates,
		ltmDnsCacheStatKeyEvictions,
		ltmDnsCacheStatUdpBytesIn,
		ltmDnsCacheStatUdpBytesOut,
		ltmDnsCacheStatUdpPktsIn,
		ltmDnsCacheStatUdpPktsOut,
		ltmDnsCacheStatUdpCurConns,
		ltmDnsCacheStatUdpMaxConns,
		ltmDnsCacheStatUdpTotConns,
		ltmDnsCacheStatTcpBytesIn,
		ltmDnsCacheStatTcpBytesOut,
		ltmDnsCacheStatTcpPktsIn,
		ltmDnsCacheStatTcpPktsOut,
		ltmDnsCacheStatTcpCurConns,
		ltmDnsCacheStatTcpMaxConns,
		ltmDnsCacheStatTcpTotConns,
		ltmDnsCacheStatUnsolicitedReplies,
		ltmDnsCacheStatSecUnchecked,
		ltmDnsCacheStatSecBogus,
		ltmDnsCacheStatSecIndeterminate,
		ltmDnsCacheStatSecInsecure,
		ltmDnsCacheStatSecSecure,
		ltmDnsCacheStatFwdQueries,
		ltmDnsCacheStatFwdResponses,
		ltmDnsCacheStatRpzRewrites
	}
	STATUS	 current
	DESCRIPTION
		"A collection of objects of ltmDnsCacheStat MIB."
	::= { bigipLocalTMGroups 115 }

ltmDnsProfileStatGroup OBJECT-GROUP
	 OBJECTS {
		ltmDnsProfileStatResetStats,
		ltmDnsProfileStatNumber,
		ltmDnsProfileStatName,
		ltmDnsProfileStatQueries,
		ltmDnsProfileStatResponses,
		ltmDnsProfileStatResponsesPerSec,
		ltmDnsProfileStatToGtm,
		ltmDnsProfileStatDnsExpressReqs,
		ltmDnsProfileStatDnsExpressNotifies,
		ltmDnsProfileStatToCache,
		ltmDnsProfileStatToDns,
		ltmDnsProfileStatDns64Reqs,
		ltmDnsProfileStatDns64Rewrites,
		ltmDnsProfileStatDns64Failures,
		ltmDnsProfileStatHints,
		ltmDnsProfileStatRejects,
		ltmDnsProfileStatNoErrors,
		ltmDnsProfileStatDrops,
		ltmDnsProfileStatMalformed,
		ltmDnsProfileStatTclSuspends,
		ltmDnsProfileStatRecursionDesired,
		ltmDnsProfileStatCheckingDisabled,
		ltmDnsProfileStatEdns0,
		ltmDnsProfileStatOpcodeQuery,
		ltmDnsProfileStatOpcodeNotify,
		ltmDnsProfileStatOpcodeUpdate,
		ltmDnsProfileStatZoneIxfr,
		ltmDnsProfileStatZoneAxfr,
		ltmDnsProfileStatAuthoritativeAnswer,
		ltmDnsProfileStatRecursionAvailable,
		ltmDnsProfileStatAuthenticatedData,
		ltmDnsProfileStatTruncated,
		ltmDnsProfileStatRcodeNoerror,
		ltmDnsProfileStatRcodeNxdomain,
		ltmDnsProfileStatRcodeServfail,
		ltmDnsProfileStatRcodeRefused,
		ltmDnsProfileStatMalicious,
		ltmDnsProfileStatAReqs,
		ltmDnsProfileStatAaaaReqs,
		ltmDnsProfileStatAnyReqs,
		ltmDnsProfileStatCnameReqs,
		ltmDnsProfileStatMxReqs,
		ltmDnsProfileStatNsReqs,
		ltmDnsProfileStatPtrReqs,
		ltmDnsProfileStatSoaReqs,
		ltmDnsProfileStatSrvReqs,
		ltmDnsProfileStatTxtReqs,
		ltmDnsProfileStatOtherReqs,
		ltmDnsProfileStatDnsEffectiveRateLimit,
		ltmDnsProfileStatDnsConfiguredObjects,
		ltmDnsProfileStatDnsRateRejectedRequests,
		ltmDnsProfileStatGtmEffectiveRateLimit,
		ltmDnsProfileStatGtmConfiguredObjects,
		ltmDnsProfileStatGtmRateRejectedRequests,
		ltmDnsProfileStatGtmRewrites,
		ltmDnsProfileStatOpcodeOther,
		ltmDnsProfileStatFastDnsQueries,
		ltmDnsProfileStatFastDnsResponses,
		ltmDnsProfileStatFastDnsAllowed,
		ltmDnsProfileStatFastDnsDrops,
		ltmDnsProfileStatFastDnsRespTc,
		ltmDnsProfileStatFastDnsRespNx,
		ltmDnsProfileStatFastDnsRespNe,
		ltmDnsProfileStatFastDnsRespRf,
		ltmDnsProfileStatHwMalformed,
		ltmDnsProfileStatHwInspected,
		ltmDnsProfileStatHwCacheLookups,
		ltmDnsProfileStatHwCacheResponses,
		ltmDnsProfileStatNaptrReqs,
		ltmDnsProfileStatRcodeBadvers,
		ltmDnsProfileStatFastDnsRespBvers
	}
	STATUS	 current
	DESCRIPTION
		"A collection of objects of ltmDnsProfileStat MIB."
	::= { bigipLocalTMGroups 116 }

ltmDosProfileGroup OBJECT-GROUP
	 OBJECTS {
		ltmDosProfileNumber,
		ltmDosProfileName,
		ltmDosProfileConfigSource,
		ltmDosProfileDefaultName
	}
	STATUS	 current
	DESCRIPTION
		"A collection of objects of ltmDosProfile MIB."
	::= { bigipLocalTMGroups 117 }

ltmDosApplicationGroup OBJECT-GROUP
	 OBJECTS {
		ltmDosApplicationNumber,
		ltmDosApplicationProfileName,
		ltmDosApplicationName,
		ltmDosApplicationTriggerIrule,
		ltmDosApplicationTpsBasedMode,
		ltmDosApplicationLatencyBasedMode,
		ltmDosApplicationTpsBasedIpClientSideDefense,
		ltmDosApplicationTpsBasedUrlClientSideDefense,
		ltmDosApplicationTpsBasedIpRateLimiting,
		ltmDosApplicationTpsBasedUrlRateLimiting,
		ltmDosApplicationTpsBasedIpTpsIncreaseRate,
		ltmDosApplicationTpsBasedIpMaximumTps,
		ltmDosApplicationTpsBasedIpMinimumTps,
		ltmDosApplicationTpsBasedUrlTpsIncreaseRate,
		ltmDosApplicationTpsBasedUrlMaximumTps,
		ltmDosApplicationTpsBasedUrlMinimumTps,
		ltmDosApplicationTpsBasedMaximumPreventionDuration,
		ltmDosApplicationLatencyIncreaseRate,
		ltmDosApplicationMaximumLatency,
		ltmDosApplicationMinimumLatency,
		ltmDosApplicationLatencyBasedIpClientSideDefense,
		ltmDosApplicationLatencyBasedUrlClientSideDefense,
		ltmDosApplicationLatencyBasedIpRateLimiting,
		ltmDosApplicationLatencyBasedUrlRateLimiting,
		ltmDosApplicationLatencyBasedIpTpsIncreaseRate,
		ltmDosApplicationLatencyBasedIpMaximumTps,
		ltmDosApplicationLatencyBasedIpMinimumTps,
		ltmDosApplicationLatencyBasedUrlTpsIncreaseRate,
		ltmDosApplicationLatencyBasedUrlMaximumTps,
		ltmDosApplicationLatencyBasedUrlMinimumTps,
		ltmDosApplicationLatencyBasedMaximumPreventionDuration,
		ltmDosApplicationTpsBasedSiteClientSideDefense,
		ltmDosApplicationTpsBasedSiteRateLimiting,
		ltmDosApplicationTpsBasedSiteTpsIncreaseRate,
		ltmDosApplicationTpsBasedSiteMaximumTps,
		ltmDosApplicationTpsBasedSiteMinimumTps,
		ltmDosApplicationTpsBasedEscalationPeriod,
		ltmDosApplicationTpsBasedDeEscalationPeriod,
		ltmDosApplicationLatencyBasedSiteClientSideDefense,
		ltmDosApplicationLatencyBasedSiteRateLimiting,
		ltmDosApplicationLatencyBasedSiteTpsIncreaseRate,
		ltmDosApplicationLatencyBasedSiteMaximumTps,
		ltmDosApplicationLatencyBasedSiteMinimumTps,
		ltmDosApplicationLatencyBasedEscalationPeriod,
		ltmDosApplicationLatencyBasedDeEscalationPeriod,
		ltmDosApplicationHeavyUrlProtection,
		ltmDosApplicationHeavyUrlAutomaticDetection,
		ltmDosApplicationHeavyUrlLatencyThreshold
	}
	STATUS	 current
	DESCRIPTION
		"A collection of objects of ltmDosApplication MIB."
	::= { bigipLocalTMGroups 118 }

ltmDosWhiteIpGroup OBJECT-GROUP
	 OBJECTS {
		ltmDosWhiteIpNumber,
		ltmDosWhiteIpParentProfile,
		ltmDosWhiteIpParentName,
		ltmDosWhiteIpAddressType,
		ltmDosWhiteIpAddress,
		ltmDosWhiteIpNetmaskType,
		ltmDosWhiteIpNetmask
	}
	STATUS	 current
	DESCRIPTION
		"A collection of objects of ltmDosWhiteIp MIB."
	::= { bigipLocalTMGroups 119 }

ltmDnsSecurityGroup OBJECT-GROUP
	 OBJECTS {
		ltmDnsSecurityNumber,
		ltmDnsSecurityName,
		ltmDnsSecurityQueryTypeInclusion
	}
	STATUS	 current
	DESCRIPTION
		"A collection of objects of ltmDnsSecurity MIB."
	::= { bigipLocalTMGroups 120 }

ltmDnsSecurityStatGroup OBJECT-GROUP
	 OBJECTS {
		ltmDnsSecurityStatResetStats,
		ltmDnsSecurityStatNumber,
		ltmDnsSecurityStatName,
		ltmDnsSecurityStatFilteredDrops,
		ltmDnsSecurityStatADrops,
		ltmDnsSecurityStatAaaaDrops,
		ltmDnsSecurityStatAnyDrops,
		ltmDnsSecurityStatCnameDrops,
		ltmDnsSecurityStatMxDrops,
		ltmDnsSecurityStatNsDrops,
		ltmDnsSecurityStatPtrDrops,
		ltmDnsSecurityStatSoaDrops,
		ltmDnsSecurityStatSrvDrops,
		ltmDnsSecurityStatTxtDrops,
		ltmDnsSecurityStatOtherDrops
	}
	STATUS	 current
	DESCRIPTION
		"A collection of objects of ltmDnsSecurityStat MIB."
	::= { bigipLocalTMGroups 121 }

ltmBwcPolicyStatGroup OBJECT-GROUP
	 OBJECTS {
		ltmBwcPolicyStatResetStats,
		ltmBwcPolicyStatNumber,
		ltmBwcPolicyStatName,
		ltmBwcPolicyStatBytesPerSec,
		ltmBwcPolicyStatBytesPerSecOut,
		ltmBwcPolicyStatBytesIn,
		ltmBwcPolicyStatBytesPassed,
		ltmBwcPolicyStatBytesDropped,
		ltmBwcPolicyStatPacketsIn,
		ltmBwcPolicyStatPacketsPassed,
		ltmBwcPolicyStatActivePolicies,
		ltmBwcPolicyStatInactivePolicies,
		ltmBwcPolicyStatTotalPolicies,
		ltmBwcPolicyStatTimeDataCollected,
		ltmBwcPolicyStatPacketsPerSec,
		ltmBwcPolicyStatPacketsPerSecOut
	}
	STATUS	 current
	DESCRIPTION
		"A collection of objects of ltmBwcPolicyStat MIB."
	::= { bigipLocalTMGroups 122 }

ltmDnsQueryFilterGroup OBJECT-GROUP
	 OBJECTS {
		ltmDnsQueryFilterNumber,
		ltmDnsQueryFilterName,
		ltmDnsQueryFilterIndex,
		ltmDnsQueryFilterType
	}
	STATUS	 current
	DESCRIPTION
		"A collection of objects of ltmDnsQueryFilter MIB."
	::= { bigipLocalTMGroups 123 }

ltmDnsHeaderFilterGroup OBJECT-GROUP
	 OBJECTS {
		ltmDnsHeaderFilterNumber,
		ltmDnsHeaderFilterName,
		ltmDnsHeaderFilterIndex,
		ltmDnsHeaderFilterOpcodeExclusion
	}
	STATUS	 current
	DESCRIPTION
		"A collection of objects of ltmDnsHeaderFilter MIB."
	::= { bigipLocalTMGroups 124 }

ltmLsnPrefixGroup OBJECT-GROUP
	 OBJECTS {
		ltmLsnPrefixNumber,
		ltmLsnPrefixName,
		ltmLsnPrefixAddrType,
		ltmLsnPrefixAddr
	}
	STATUS	 current
	DESCRIPTION
		"A collection of objects of ltmLsnPrefix MIB."
	::= { bigipLocalTMGroups 125 }

ltmLsnPoolGroup OBJECT-GROUP
	 OBJECTS {
		ltmLsnPoolNumber,
		ltmLsnPoolName,
		ltmLsnPoolMemberCount,
		ltmLsnPoolRouteAdvertisement,
		ltmLsnPoolMode,
		ltmLsnPoolPersistenceMode,
		ltmLsnPoolPersistenceTimeout,
		ltmLsnPoolPersistencePrefixLengthIpv4,
		ltmLsnPoolPersistencePrefixLengthIpv6,
		ltmLsnPoolInboundConnections,
		ltmLsnPoolIcmpEcho,
		ltmLsnPoolTranslationPortRangeLow,
		ltmLsnPoolTranslationPortRangeHigh,
		ltmLsnPoolClientConnectionLimit,
		ltmLsnPoolEgressInterfacesEnabled,
		ltmLsnPoolLogPublisher,
		ltmLsnPoolHairpinMode,
		ltmLsnPoolLogProfile
	}
	STATUS	 current
	DESCRIPTION
		"A collection of objects of ltmLsnPool MIB."
	::= { bigipLocalTMGroups 126 }

ltmLsnPrefixLsnPoolGroup OBJECT-GROUP
	 OBJECTS {
		ltmLsnPrefixLsnPoolNumber,
		ltmLsnPrefixLsnPoolLsnPrefixName,
		ltmLsnPrefixLsnPoolLsnPoolName,
		ltmLsnPrefixLsnPoolPrefixAddressType,
		ltmLsnPrefixLsnPoolPrefixAddress
	}
	STATUS	 current
	DESCRIPTION
		"A collection of objects of ltmLsnPrefixLsnPool MIB."
	::= { bigipLocalTMGroups 127 }

ltmLsnPrefixLsnPoolBackupGroup OBJECT-GROUP
	 OBJECTS {
		ltmLsnPrefixLsnPoolBackupNumber,
		ltmLsnPrefixLsnPoolBackupLsnPrefixName,
		ltmLsnPrefixLsnPoolBackupLsnPoolName,
		ltmLsnPrefixLsnPoolBackupPrefixAddressType,
		ltmLsnPrefixLsnPoolBackupPrefixAddress
	}
	STATUS	 current
	DESCRIPTION
		"A collection of objects of ltmLsnPrefixLsnPoolBackup MIB."
	::= { bigipLocalTMGroups 128 }

ltmLsnPoolVlanGroup OBJECT-GROUP
	 OBJECTS {
		ltmLsnPoolVlanNumber,
		ltmLsnPoolVlanLsnPoolName,
		ltmLsnPoolVlanVlanName
	}
	STATUS	 current
	DESCRIPTION
		"A collection of objects of ltmLsnPoolVlan MIB."
	::= { bigipLocalTMGroups 129 }

ltmLsnPoolStatGroup OBJECT-GROUP
	 OBJECTS {
		ltmLsnPoolStatResetStats,
		ltmLsnPoolStatNumber,
		ltmLsnPoolStatName,
		ltmLsnPoolStatTranslationRequests,
		ltmLsnPoolStatHairpinConnectionRequests,
		ltmLsnPoolStatActiveTranslations,
		ltmLsnPoolStatActiveHairpinConnections,
		ltmLsnPoolStatTranslationRequestFailures,
		ltmLsnPoolStatPersistenceMappingFailures,
		ltmLsnPoolStatHairpinConnectionFailures,
		ltmLsnPoolStatBackupPoolTranslations,
		ltmLsnPoolStatLogAttempts,
		ltmLsnPoolStatLogFailures,
		ltmLsnPoolStatTotalEndPoints,
		ltmLsnPoolStatPcpAnnounceRequests,
		ltmLsnPoolStatPcpAnnounceResponsesUcast,
		ltmLsnPoolStatPcpAnnounceResponsesMulticast,
		ltmLsnPoolStatPcpMapRequests,
		ltmLsnPoolStatPcpMapResponses,
		ltmLsnPoolStatPcpPeerRequests,
		ltmLsnPoolStatPcpPeerResponses,
		ltmLsnPoolStatPcpErrorsInvalidRequest,
		ltmLsnPoolStatPcpErrorsUnavailableResource,
		ltmLsnPoolStatPcpErrorsNotAuthorized,
		ltmLsnPoolStatPcpErrorsOther,
		ltmLsnPoolStatActivePortBlocks,
		ltmLsnPoolStatActiveClientsReachedLimit,
		ltmLsnPoolStatActiveZombiePortBlocks,
		ltmLsnPoolStatTotalClientsReachedLimit,
		ltmLsnPoolStatTotalPortBlockAllocations,
		ltmLsnPoolStatTotalPortBlockAllocationFailures,
		ltmLsnPoolStatTotalPortBlockDeallocations,
		ltmLsnPoolStatTotalZombiePortBlocksCreated,
		ltmLsnPoolStatTotalZombiePortBlocksDeleted,
		ltmLsnPoolStatTotalZombiePortBlockConnsKilled,
		ltmLsnPoolStatEndPointsString,
		ltmLsnPoolStatTotalPortBlocks,
		ltmLsnPoolStatPercentFreePortBlocksSnmp
	}
	STATUS	 current
	DESCRIPTION
		"A collection of objects of ltmLsnPoolStat MIB."
	::= { bigipLocalTMGroups 130 }

ltmSpdyProfileGroup OBJECT-GROUP
	 OBJECTS {
		ltmSpdyProfileNumber,
		ltmSpdyProfileName,
		ltmSpdyProfileConfigSource,
		ltmSpdyProfileDefaultName,
		ltmSpdyProfileActivationMode,
		ltmSpdyProfilePriorityHandling,
		ltmSpdyProfileInsertHeader,
		ltmSpdyProfileInsertHeaderName,
		ltmSpdyProfileConcurrentStreamsPerConnection,
		ltmSpdyProfileConnectionIdleTimeout,
		ltmSpdyProfileReceiveWindow,
		ltmSpdyProfileFrameSize,
		ltmSpdyProfileWriteSize,
		ltmSpdyProfileCompressionLevel,
		ltmSpdyProfileCompressionWindowSize
	}
	STATUS	 current
	DESCRIPTION
		"A collection of objects of ltmSpdyProfile MIB."
	::= { bigipLocalTMGroups 131 }

ltmSpdyProfileProtocolVersionsGroup OBJECT-GROUP
	 OBJECTS {
		ltmSpdyProfileProtocolVersionsNumber,
		ltmSpdyProfileProtocolVersionsName,
		ltmSpdyProfileProtocolVersionsIndex,
		ltmSpdyProfileProtocolVersionsProtocolVersions
	}
	STATUS	 current
	DESCRIPTION
		"A collection of objects of ltmSpdyProfileProtocolVersions MIB."
	::= { bigipLocalTMGroups 132 }

ltmSpdyProfileStatGroup OBJECT-GROUP
	 OBJECTS {
		ltmSpdyProfileStatResetStats,
		ltmSpdyProfileStatNumber,
		ltmSpdyProfileStatName,
		ltmSpdyProfileStatConnectionsAccepted,
		ltmSpdyProfileStatConnectionsCurrent,
		ltmSpdyProfileStatConnectionsMax,
		ltmSpdyProfileStatDataFramesReceived,
		ltmSpdyProfileStatDataFramesSent,
		ltmSpdyProfileStatFlowsCreated,
		ltmSpdyProfileStatFlowsCurrent,
		ltmSpdyProfileStatFlowsMax,
		ltmSpdyProfileStatGoawayFramesReceived,
		ltmSpdyProfileStatGoawayFramesSent,
		ltmSpdyProfileStatHeadersFramesReceived,
		ltmSpdyProfileStatHeadersFramesSent,
		ltmSpdyProfileStatHttpRequestBytes,
		ltmSpdyProfileStatHttpResponseBytes,
		ltmSpdyProfileStatNoopFramesReceived,
		ltmSpdyProfileStatNoopFramesSent,
		ltmSpdyProfileStatPingFramesReceived,
		ltmSpdyProfileStatPingFramesSent,
		ltmSpdyProfileStatRstStreamFramesReceived,
		ltmSpdyProfileStatRstStreamFramesSent,
		ltmSpdyProfileStatSettingsFramesReceived,
		ltmSpdyProfileStatSettingsFramesSent,
		ltmSpdyProfileStatSpdyRequestBytes,
		ltmSpdyProfileStatSpdyRequestFrames,
		ltmSpdyProfileStatSpdyResponseBytes,
		ltmSpdyProfileStatSpdyResponseFrames,
		ltmSpdyProfileStatSynReplyFramesReceived,
		ltmSpdyProfileStatSynReplyFramesSent,
		ltmSpdyProfileStatSynStreamFramesReceived,
		ltmSpdyProfileStatSynStreamFramesSent,
		ltmSpdyProfileStatV2StreamsCreated,
		ltmSpdyProfileStatV2StreamsCurrent,
		ltmSpdyProfileStatV2StreamsMax,
		ltmSpdyProfileStatV3StreamsCreated,
		ltmSpdyProfileStatV3StreamsCurrent,
		ltmSpdyProfileStatV3StreamsMax,
		ltmSpdyProfileStatWindowUpdateFramesReceived,
		ltmSpdyProfileStatWindowUpdateFramesSent
	}
	STATUS	 current
	DESCRIPTION
		"A collection of objects of ltmSpdyProfileStat MIB."
	::= { bigipLocalTMGroups 133 }

ltmFtpProfileStatGroup OBJECT-GROUP
	 OBJECTS {
		ltmFtpProfileStatResetStats,
		ltmFtpProfileStatNumber,
		ltmFtpProfileStatName,
		ltmFtpProfileStatLoginRequests,
		ltmFtpProfileStatDownloadRequests,
		ltmFtpProfileStatUploadRequests,
		ltmFtpProfileStatFtpsSessions,
		ltmFtpProfileStatPassthruTransitions,
		ltmFtpProfileStatFtpsIntercepts,
		ltmFtpProfileStatFtpsResets,
		ltmFtpProfileStatFtpsBypasses,
		ltmFtpProfileStatPassiveRequests,
		ltmFtpProfileStatActiveRequests
	}
	STATUS	 current
	DESCRIPTION
		"A collection of objects of ltmFtpProfileStat MIB."
	::= { bigipLocalTMGroups 134 }

ltmDosApplicationHeavyUrlInclGroup OBJECT-GROUP
	 OBJECTS {
		ltmDosApplicationHeavyUrlInclNumber,
		ltmDosApplicationHeavyUrlInclProfileName,
		ltmDosApplicationHeavyUrlInclName,
		ltmDosApplicationHeavyUrlInclIndex,
		ltmDosApplicationHeavyUrlInclUrl
	}
	STATUS	 current
	DESCRIPTION
		"A collection of objects of ltmDosApplicationHeavyUrlIncl MIB."
	::= { bigipLocalTMGroups 135 }

ltmDosApplicationHeavyUrlExclGroup OBJECT-GROUP
	 OBJECTS {
		ltmDosApplicationHeavyUrlExclNumber,
		ltmDosApplicationHeavyUrlExclProfileName,
		ltmDosApplicationHeavyUrlExclName,
		ltmDosApplicationHeavyUrlExclIndex,
		ltmDosApplicationHeavyUrlExclUrl
	}
	STATUS	 current
	DESCRIPTION
		"A collection of objects of ltmDosApplicationHeavyUrlExcl MIB."
	::= { bigipLocalTMGroups 136 }

ltmV6rdProfileGroup OBJECT-GROUP
	 OBJECTS {
		ltmV6rdProfileNumber,
		ltmV6rdProfileName,
		ltmV6rdProfileConfigSource,
		ltmV6rdProfileDefaultName,
		ltmV6rdProfileIpv4prefixType,
		ltmV6rdProfileIpv4prefix,
		ltmV6rdProfileIpv4prefixlen,
		ltmV6rdProfileV6rdprefixType,
		ltmV6rdProfileV6rdprefix,
		ltmV6rdProfileV6rdprefixlen
	}
	STATUS	 current
	DESCRIPTION
		"A collection of objects of ltmV6rdProfile MIB."
	::= { bigipLocalTMGroups 137 }

ltmPptpProfileGroup OBJECT-GROUP
	 OBJECTS {
		ltmPptpProfileNumber,
		ltmPptpProfileName,
		ltmPptpProfileDescription,
		ltmPptpProfileConfigSource,
		ltmPptpProfileDefaultName,
		ltmPptpProfileLogServerIp,
		ltmPptpProfileLogPublisher,
		ltmPptpProfileCsvFormat
	}
	STATUS	 current
	DESCRIPTION
		"A collection of objects of ltmPptpProfile MIB."
	::= { bigipLocalTMGroups 138 }

ltmPptpProfileStatGroup OBJECT-GROUP
	 OBJECTS {
		ltmPptpProfileStatResetStats,
		ltmPptpProfileStatNumber,
		ltmPptpProfileStatName,
		ltmPptpProfileStatStartRequests,
		ltmPptpProfileStatStartReplies,
		ltmPptpProfileStatStopRequests,
		ltmPptpProfileStatStopReplies,
		ltmPptpProfileStatEchoRequests,
		ltmPptpProfileStatEchoReplies,
		ltmPptpProfileStatOutgoingCallRequests,
		ltmPptpProfileStatOutgoingCallReplies,
		ltmPptpProfileStatCallClearRequests,
		ltmPptpProfileStatCallDisconnectNotifies,
		ltmPptpProfileStatWanErrorNotifies,
		ltmPptpProfileStatSetLinkInfo,
		ltmPptpProfileStatActiveCalls,
		ltmPptpProfileStatTotalCalls,
		ltmPptpProfileStatFailedCalls
	}
	STATUS	 current
	DESCRIPTION
		"A collection of objects of ltmPptpProfileStat MIB."
	::= { bigipLocalTMGroups 139 }

ltmPcpProfileGroup OBJECT-GROUP
	 OBJECTS {
		ltmPcpProfileNumber,
		ltmPcpProfileName,
		ltmPcpProfileConfigSource,
		ltmPcpProfileDefaultName,
		ltmPcpProfileListeningPort,
		ltmPcpProfileMulticastPort,
		ltmPcpProfileMinMappingLifetime,
		ltmPcpProfileMaxMappingLifetime,
		ltmPcpProfileMapRecycleDelay,
		ltmPcpProfileMapLimitPerClient,
		ltmPcpProfileMapFilterLimit,
		ltmPcpProfileThirdPartyOption,
		ltmPcpProfileRuleName
	}
	STATUS	 current
	DESCRIPTION
		"A collection of objects of ltmPcpProfile MIB."
	::= { bigipLocalTMGroups 140 }

ltmPcpPrefixGroup OBJECT-GROUP
	 OBJECTS {
		ltmPcpPrefixNumber,
		ltmPcpPrefixName,
		ltmPcpPrefixAddrType,
		ltmPcpPrefixAddr
	}
	STATUS	 current
	DESCRIPTION
		"A collection of objects of ltmPcpPrefix MIB."
	::= { bigipLocalTMGroups 141 }

ltmPcpPrefixProfilePcpGroup OBJECT-GROUP
	 OBJECTS {
		ltmPcpPrefixProfilePcpNumber,
		ltmPcpPrefixProfilePcpPcpPrefixName,
		ltmPcpPrefixProfilePcpName,
		ltmPcpPrefixProfilePcpPrefixAddressType,
		ltmPcpPrefixProfilePcpPrefixAddress
	}
	STATUS	 current
	DESCRIPTION
		"A collection of objects of ltmPcpPrefixProfilePcp MIB."
	::= { bigipLocalTMGroups 142 }

ltmPcpProfileStatGroup OBJECT-GROUP
	 OBJECTS {
		ltmPcpProfileStatResetStats,
		ltmPcpProfileStatNumber,
		ltmPcpProfileStatName,
		ltmPcpProfileStatPcpAnnounceRequests,
		ltmPcpProfileStatPcpAnnounceResponsesUcast,
		ltmPcpProfileStatPcpAnnounceResponsesMulticast,
		ltmPcpProfileStatPcpMapRequests,
		ltmPcpProfileStatPcpMapResponses,
		ltmPcpProfileStatPcpPeerRequests,
		ltmPcpProfileStatPcpPeerResponses,
		ltmPcpProfileStatPcpErrorsInvalidRequest,
		ltmPcpProfileStatPcpErrorsUnavailableResource,
		ltmPcpProfileStatPcpErrorsNotAuthorized,
		ltmPcpProfileStatPcpErrorsOther
	}
	STATUS	 current
	DESCRIPTION
		"A collection of objects of ltmPcpProfileStat MIB."
	::= { bigipLocalTMGroups 143 }

ltmDnsExpressStatGroup OBJECT-GROUP
	 OBJECTS {
		ltmDnsExpressStatResetStats,
		ltmDnsExpressStatNumber,
		ltmDnsExpressStatName,
		ltmDnsExpressStatDnsxQueries,
		ltmDnsExpressStatDnsxResponses,
		ltmDnsExpressStatDnsxNotifiesRecv,
		ltmDnsExpressStatAxfrQueries,
		ltmDnsExpressStatIxfrQueries,
		ltmDnsExpressStatXfrQueriesAclFailed,
		ltmDnsExpressStatXfrNotifiesSent,
		ltmDnsExpressStatDnsxXfrMsgs,
		ltmDnsExpressStatXfrNotifiesFailed,
		ltmDnsExpressStatTsigMissing,
		ltmDnsExpressStatTsigNotRequired,
		ltmDnsExpressStatTsigVerified,
		ltmDnsExpressStatTsigBadKey,
		ltmDnsExpressStatTsigBadSig,
		ltmDnsExpressStatTsigBadTime
	}
	STATUS	 current
	DESCRIPTION
		"A collection of objects of ltmDnsExpressStat MIB."
	::= { bigipLocalTMGroups 144 }

ltmDnsServerStatGroup OBJECT-GROUP
	 OBJECTS {
		ltmDnsServerStatResetStats,
		ltmDnsServerStatNumber,
		ltmDnsServerStatName,
		ltmDnsServerStatXfrQueries,
		ltmDnsServerStatXfrResponses,
		ltmDnsServerStatXfrNotifies,
		ltmDnsServerStatXfrNotifyFailed
	}
	STATUS	 current
	DESCRIPTION
		"A collection of objects of ltmDnsServerStat MIB."
	::= { bigipLocalTMGroups 145 }

ltmDnsCacheForwardZoneGroup OBJECT-GROUP
	 OBJECTS {
		ltmDnsCacheForwardZoneNumber,
		ltmDnsCacheForwardZoneName,
		ltmDnsCacheForwardZoneCacheName
	}
	STATUS	 current
	DESCRIPTION
		"A collection of objects of ltmDnsCacheForwardZone MIB."
	::= { bigipLocalTMGroups 146 }

ltmDnsCacheForwardZoneNameServerGroup OBJECT-GROUP
	 OBJECTS {
		ltmDnsCacheForwardZoneNameServerNumber,
		ltmDnsCacheForwardZoneNameServerAddrType,
		ltmDnsCacheForwardZoneNameServerAddr,
		ltmDnsCacheForwardZoneNameServerPort,
		ltmDnsCacheForwardZoneNameServerForwardZoneName,
		ltmDnsCacheForwardZoneNameServerCacheName
	}
	STATUS	 current
	DESCRIPTION
		"A collection of objects of ltmDnsCacheForwardZoneNameServer MIB."
	::= { bigipLocalTMGroups 147 }

ltmClientSslCertKeyChainGroup OBJECT-GROUP
	 OBJECTS {
		ltmClientSslCertKeyChainNumber,
		ltmClientSslCertKeyChainName,
		ltmClientSslCertKeyChainClientssl,
		ltmClientSslCertKeyChainCert,
		ltmClientSslCertKeyChainKey,
		ltmClientSslCertKeyChainChain,
		ltmClientSslCertKeyChainOcspStplParams
	}
	STATUS	 current
	DESCRIPTION
		"A collection of objects of ltmClientSslCertKeyChain MIB."
	::= { bigipLocalTMGroups 148 }

ltmDosAttackDataStatGroup OBJECT-GROUP
	 OBJECTS {
		ltmDosAttackDataStatResetStats,
		ltmDosAttackDataStatNumber,
		ltmDosAttackDataStatDeviceName,
		ltmDosAttackDataStatVectorName,
		ltmDosAttackDataStatAttackType,
		ltmDosAttackDataStatAttackDetected,
		ltmDosAttackDataStatAttackCount,
		ltmDosAttackDataStatStats,
		ltmDosAttackDataStatStatsRate,
		ltmDosAttackDataStatStats1m,
		ltmDosAttackDataStatStats1h,
		ltmDosAttackDataStatDrops,
		ltmDosAttackDataStatDropsRate,
		ltmDosAttackDataStatDrops1m,
		ltmDosAttackDataStatDrops1h,
		ltmDosAttackDataStatWlCount
	}
	STATUS	 current
	DESCRIPTION
		"A collection of objects of ltmDosAttackDataStat MIB."
	::= { bigipLocalTMGroups 149 }

ltmNetworkAttackDataStatGroup OBJECT-GROUP
	 OBJECTS {
		ltmNetworkAttackDataStatResetStats,
		ltmNetworkAttackDataStatNumber,
		ltmNetworkAttackDataStatProfileName,
		ltmNetworkAttackDataStatVsName,
		ltmNetworkAttackDataStatVectorName,
		ltmNetworkAttackDataStatAttackType,
		ltmNetworkAttackDataStatAttackDetected,
		ltmNetworkAttackDataStatAttackCount,
		ltmNetworkAttackDataStatStats,
		ltmNetworkAttackDataStatStatsRate,
		ltmNetworkAttackDataStatStats1m,
		ltmNetworkAttackDataStatStats1h,
		ltmNetworkAttackDataStatDrops,
		ltmNetworkAttackDataStatDropsRate,
		ltmNetworkAttackDataStatDrops1m,
		ltmNetworkAttackDataStatDrops1h,
		ltmNetworkAttackDataStatWlCount
	}
	STATUS	 current
	DESCRIPTION
		"A collection of objects of ltmNetworkAttackDataStat MIB."
	::= { bigipLocalTMGroups 150 }

ltmFwAdminIpRuleStatGroup OBJECT-GROUP
	 OBJECTS {
		ltmFwAdminIpRuleStatNumber,
		ltmFwAdminIpRuleStatRuleName,
		ltmFwAdminIpRuleStatContainerName,
		ltmFwAdminIpRuleStatCounter
	}
	STATUS	 current
	DESCRIPTION
		"A collection of objects of ltmFwAdminIpRuleStat MIB."
	::= { bigipLocalTMGroups 151 }

ltmFwIpintGlobalStatGroup OBJECT-GROUP
	 OBJECTS {
		ltmFwIpintGlobalStatResetStats,
		ltmFwIpintGlobalStatNumber,
		ltmFwIpintGlobalStatBlClassName,
		ltmFwIpintGlobalStatSrcIpBlacklist,
		ltmFwIpintGlobalStatDstIpBlacklist
	}
	STATUS	 current
	DESCRIPTION
		"A collection of objects of ltmFwIpintGlobalStat MIB."
	::= { bigipLocalTMGroups 152 }

ltmFwIpintVirtualStatGroup OBJECT-GROUP
	 OBJECTS {
		ltmFwIpintVirtualStatResetStats,
		ltmFwIpintVirtualStatNumber,
		ltmFwIpintVirtualStatContextName,
		ltmFwIpintVirtualStatBlClassName,
		ltmFwIpintVirtualStatSrcIpBlacklist,
		ltmFwIpintVirtualStatDstIpBlacklist
	}
	STATUS	 current
	DESCRIPTION
		"A collection of objects of ltmFwIpintVirtualStat MIB."
	::= { bigipLocalTMGroups 153 }

ltmFwIpintRouteDomainStatGroup OBJECT-GROUP
	 OBJECTS {
		ltmFwIpintRouteDomainStatResetStats,
		ltmFwIpintRouteDomainStatNumber,
		ltmFwIpintRouteDomainStatContextName,
		ltmFwIpintRouteDomainStatBlClassName,
		ltmFwIpintRouteDomainStatSrcIpBlacklist,
		ltmFwIpintRouteDomainStatDstIpBlacklist
	}
	STATUS	 current
	DESCRIPTION
		"A collection of objects of ltmFwIpintRouteDomainStat MIB."
	::= { bigipLocalTMGroups 154 }

ltmRouteDomainStatGroup OBJECT-GROUP
	 OBJECTS {
		ltmRouteDomainStatResetStats,
		ltmRouteDomainStatNumber,
		ltmRouteDomainStatName,
		ltmRouteDomainStatConnLimit,
		ltmRouteDomainStatConnectionFlowMiss,
		ltmRouteDomainStatClientPktsIn,
		ltmRouteDomainStatClientBytesIn,
		ltmRouteDomainStatClientPktsOut,
		ltmRouteDomainStatClientBytesOut,
		ltmRouteDomainStatClientMaxConns,
		ltmRouteDomainStatClientTotConns,
		ltmRouteDomainStatClientCurConns,
		ltmRouteDomainStatClientEvictedConns,
		ltmRouteDomainStatClientSlowKilled,
		ltmRouteDomainStatServerPktsIn,
		ltmRouteDomainStatServerBytesIn,
		ltmRouteDomainStatServerPktsOut,
		ltmRouteDomainStatServerBytesOut,
		ltmRouteDomainStatServerMaxConns,
		ltmRouteDomainStatServerTotConns,
		ltmRouteDomainStatServerCurConns,
		ltmRouteDomainStatServerEvictedConns,
		ltmRouteDomainStatServerSlowKilled
	}
	STATUS	 current
	DESCRIPTION
		"A collection of objects of ltmRouteDomainStat MIB."
	::= { bigipLocalTMGroups 155 }

ltmFlowEvictionPolicyStatGroup OBJECT-GROUP
	 OBJECTS {
		ltmFlowEvictionPolicyStatResetStats,
		ltmFlowEvictionPolicyStatNumber,
		ltmFlowEvictionPolicyStatPolicyName,
		ltmFlowEvictionPolicyStatSweptContext,
		ltmFlowEvictionPolicyStatContextName,
		ltmFlowEvictionPolicyStatEvicted
	}
	STATUS	 current
	DESCRIPTION
		"A collection of objects of ltmFlowEvictionPolicyStat MIB."
	::= { bigipLocalTMGroups 156 }

ltmAlgLogProfileGroup OBJECT-GROUP
	 OBJECTS {
		ltmAlgLogProfileNumber,
		ltmAlgLogProfileName,
		ltmAlgLogProfileDescription,
		ltmAlgLogProfileConfigSource,
		ltmAlgLogProfileDefaultName,
		ltmAlgLogProfileStartControlAction,
		ltmAlgLogProfileEndControlAction,
		ltmAlgLogProfileStartDataAction,
		ltmAlgLogProfileEndDataAction,
		ltmAlgLogProfileInboundAction,
		ltmAlgLogProfileCsvFormat
	}
	STATUS	 current
	DESCRIPTION
		"A collection of objects of ltmAlgLogProfile MIB."
	::= { bigipLocalTMGroups 157 }

ltmAlgLogProfileStartControlElementsGroup OBJECT-GROUP
	 OBJECTS {
		ltmAlgLogProfileStartControlElementsNumber,
		ltmAlgLogProfileStartControlElementsName,
		ltmAlgLogProfileStartControlElementsIndex,
		ltmAlgLogProfileStartControlElementsElements
	}
	STATUS	 current
	DESCRIPTION
		"A collection of objects of ltmAlgLogProfileStartControlElements MIB."
	::= { bigipLocalTMGroups 158 }

ltmAlgLogProfileEndControlElementsGroup OBJECT-GROUP
	 OBJECTS {
		ltmAlgLogProfileEndControlElementsNumber,
		ltmAlgLogProfileEndControlElementsName,
		ltmAlgLogProfileEndControlElementsIndex,
		ltmAlgLogProfileEndControlElementsElements
	}
	STATUS	 current
	DESCRIPTION
		"A collection of objects of ltmAlgLogProfileEndControlElements MIB."
	::= { bigipLocalTMGroups 159 }

ltmAlgLogProfileStartDataElementsGroup OBJECT-GROUP
	 OBJECTS {
		ltmAlgLogProfileStartDataElementsNumber,
		ltmAlgLogProfileStartDataElementsName,
		ltmAlgLogProfileStartDataElementsIndex,
		ltmAlgLogProfileStartDataElementsElements
	}
	STATUS	 current
	DESCRIPTION
		"A collection of objects of ltmAlgLogProfileStartDataElements MIB."
	::= { bigipLocalTMGroups 160 }

ltmAlgLogProfileEndDataElementsGroup OBJECT-GROUP
	 OBJECTS {
		ltmAlgLogProfileEndDataElementsNumber,
		ltmAlgLogProfileEndDataElementsName,
		ltmAlgLogProfileEndDataElementsIndex,
		ltmAlgLogProfileEndDataElementsElements
	}
	STATUS	 current
	DESCRIPTION
		"A collection of objects of ltmAlgLogProfileEndDataElements MIB."
	::= { bigipLocalTMGroups 161 }

ltmLsnLogProfileGroup OBJECT-GROUP
	 OBJECTS {
		ltmLsnLogProfileNumber,
		ltmLsnLogProfileName,
		ltmLsnLogProfileDescription,
		ltmLsnLogProfileConfigSource,
		ltmLsnLogProfileDefaultName,
		ltmLsnLogProfileStartOutboundAction,
		ltmLsnLogProfileEndOutboundAction,
		ltmLsnLogProfileStartInboundAction,
		ltmLsnLogProfileEndInboundAction,
		ltmLsnLogProfileQuotaExceededAction,
		ltmLsnLogProfileErrorsAction,
		ltmLsnLogProfileCsvFormat
	}
	STATUS	 current
	DESCRIPTION
		"A collection of objects of ltmLsnLogProfile MIB."
	::= { bigipLocalTMGroups 162 }

ltmLsnLogProfileStartOutboundElementsGroup OBJECT-GROUP
	 OBJECTS {
		ltmLsnLogProfileStartOutboundElementsNumber,
		ltmLsnLogProfileStartOutboundElementsName,
		ltmLsnLogProfileStartOutboundElementsIndex,
		ltmLsnLogProfileStartOutboundElementsElements
	}
	STATUS	 current
	DESCRIPTION
		"A collection of objects of ltmLsnLogProfileStartOutboundElements MIB."
	::= { bigipLocalTMGroups 163 }

ltmLsnLogProfileEndOutboundElementsGroup OBJECT-GROUP
	 OBJECTS {
		ltmLsnLogProfileEndOutboundElementsNumber,
		ltmLsnLogProfileEndOutboundElementsName,
		ltmLsnLogProfileEndOutboundElementsIndex,
		ltmLsnLogProfileEndOutboundElementsElements
	}
	STATUS	 current
	DESCRIPTION
		"A collection of objects of ltmLsnLogProfileEndOutboundElements MIB."
	::= { bigipLocalTMGroups 164 }

ltmOcspStaplingParametersGroup OBJECT-GROUP
	 OBJECTS {
		ltmOcspStaplingParametersNumber,
		ltmOcspStaplingParametersName,
		ltmOcspStaplingParametersUseProxyServer,
		ltmOcspStaplingParametersProxyServerPool,
		ltmOcspStaplingParametersDnsResolver,
		ltmOcspStaplingParametersTrustedCa,
		ltmOcspStaplingParametersTrustedResponders,
		ltmOcspStaplingParametersUrl,
		ltmOcspStaplingParametersSignerCert,
		ltmOcspStaplingParametersSignerKey,
		ltmOcspStaplingParametersSignHash,
		ltmOcspStaplingParametersTimeout,
		ltmOcspStaplingParametersClockSkew,
		ltmOcspStaplingParametersStatusAge,
		ltmOcspStaplingParametersCacheTimeout,
		ltmOcspStaplingParametersCacheErrorTimeout,
		ltmOcspStaplingParametersStrictRespCertCheck
	}
	STATUS	 current
	DESCRIPTION
		"A collection of objects of ltmOcspStaplingParameters MIB."
	::= { bigipLocalTMGroups 165 }

ltmFwRuleStatGroup OBJECT-GROUP
	 OBJECTS {
		ltmFwRuleStatNumber,
		ltmFwRuleStatContextType,
		ltmFwRuleStatContextName,
		ltmFwRuleStatRuleName,
		ltmFwRuleStatRuleListName,
		ltmFwRuleStatPolicyName,
		ltmFwRuleStatRuleStatType,
		ltmFwRuleStatActualRule,
		ltmFwRuleStatCounter,
		ltmFwRuleStatLastHitTime,
		ltmFwRuleStatLastHitTimeFmt,
		ltmFwRuleStatOverlapper,
		ltmFwRuleStatOverlapType,
		ltmFwRuleStatAction
	}
	STATUS	 current
	DESCRIPTION
		"A collection of objects of ltmFwRuleStat MIB."
	::= { bigipLocalTMGroups 166 }

ltmFwContextStatGroup OBJECT-GROUP
	 OBJECTS {
		ltmFwContextStatNumber,
		ltmFwContextStatContextType,
		ltmFwContextStatContextName,
		ltmFwContextStatEnforcedPacketsAccept,
		ltmFwContextStatEnforcedPacketsAcceptDecisively,
		ltmFwContextStatEnforcedPacketsReject,
		ltmFwContextStatEnforcedPacketsDrop,
		ltmFwContextStatEnforcedPacketsDefaultAccept,
		ltmFwContextStatEnforcedPacketsDefaultReject,
		ltmFwContextStatEnforcedPacketsDefaultDrop,
		ltmFwContextStatStagedPacketsAccept,
		ltmFwContextStatStagedPacketsAcceptDecisively,
		ltmFwContextStatStagedPacketsReject,
		ltmFwContextStatStagedPacketsDrop,
		ltmFwContextStatStagedPacketsDefaultAccept,
		ltmFwContextStatStagedPacketsDefaultReject,
		ltmFwContextStatStagedPacketsDefaultDrop
	}
	STATUS	 current
	DESCRIPTION
		"A collection of objects of ltmFwContextStat MIB."
	::= { bigipLocalTMGroups 167 }

ltmFwPolicyRuleStatGroup OBJECT-GROUP
	 OBJECTS {
		ltmFwPolicyRuleStatNumber,
		ltmFwPolicyRuleStatContextType,
		ltmFwPolicyRuleStatContextName,
		ltmFwPolicyRuleStatRuleName,
		ltmFwPolicyRuleStatRuleListName,
		ltmFwPolicyRuleStatPolicyName,
		ltmFwPolicyRuleStatRuleStatType,
		ltmFwPolicyRuleStatActualRule,
		ltmFwPolicyRuleStatCounter,
		ltmFwPolicyRuleStatLastHitTime,
		ltmFwPolicyRuleStatLastHitTimeFmt,
		ltmFwPolicyRuleStatOverlapper,
		ltmFwPolicyRuleStatOverlapType
	}
	STATUS	 current
	DESCRIPTION
		"A collection of objects of ltmFwPolicyRuleStat MIB."
	::= { bigipLocalTMGroups 168 }

ltmTftpProfileGroup OBJECT-GROUP
	 OBJECTS {
		ltmTftpProfileNumber,
		ltmTftpProfileName,
		ltmTftpProfileConfigSource,
		ltmTftpProfileDefaultName,
		ltmTftpProfileIdleTimeout,
		ltmTftpProfileLogPublisher,
		ltmTftpProfileLogProfile
	}
	STATUS	 current
	DESCRIPTION
		"A collection of objects of ltmTftpProfile MIB."
	::= { bigipLocalTMGroups 169 }

ltmTftpProfileStatGroup OBJECT-GROUP
	 OBJECTS {
		ltmTftpProfileStatResetStats,
		ltmTftpProfileStatNumber,
		ltmTftpProfileStatName,
		ltmTftpProfileStatReadRequests,
		ltmTftpProfileStatWriteRequests,
		ltmTftpProfileStatDiscardedRequests
	}
	STATUS	 current
	DESCRIPTION
		"A collection of objects of ltmTftpProfileStat MIB."
	::= { bigipLocalTMGroups 170 }

ltmIpsecalgProfileGroup OBJECT-GROUP
	 OBJECTS {
		ltmIpsecalgProfileNumber,
		ltmIpsecalgProfileName,
		ltmIpsecalgProfileConfigSource,
		ltmIpsecalgProfileDefaultName,
		ltmIpsecalgProfileIdleTimeout,
		ltmIpsecalgProfilePendingIkeConnectionLimit,
		ltmIpsecalgProfileInitialConnectionTimeout,
		ltmIpsecalgProfileLogPublisher,
		ltmIpsecalgProfileLogProfile
	}
	STATUS	 current
	DESCRIPTION
		"A collection of objects of ltmIpsecalgProfile MIB."
	::= { bigipLocalTMGroups 171 }

ltmKnownMethodsGroup OBJECT-GROUP
	 OBJECTS {
		ltmKnownMethodsNumber,
		ltmKnownMethodsName,
		ltmKnownMethodsIndex,
		ltmKnownMethodsStr
	}
	STATUS	 current
	DESCRIPTION
		"A collection of objects of ltmHttpProfileKnownMethods MIB."
	::= { bigipLocalTMGroups 172 }

ltmIpsecalgProfileStatGroup OBJECT-GROUP
	 OBJECTS {
		ltmIpsecalgProfileStatResetStats,
		ltmIpsecalgProfileStatNumber,
		ltmIpsecalgProfileStatName,
		ltmIpsecalgProfileStatIkePackets,
		ltmIpsecalgProfileStatTunnelCreates,
		ltmIpsecalgProfileStatTunnelTeardowns,
		ltmIpsecalgProfileStatFailures,
		ltmIpsecalgProfileStatPendingIkeConnectionLimitDrops
	}
	STATUS	 current
	DESCRIPTION
		"A collection of objects of ltmIpsecalgProfileStat MIB."
	::= { bigipLocalTMGroups 173 }

ltmHttp2ProfileGroup OBJECT-GROUP
	 OBJECTS {
		ltmHttp2ProfileNumber,
		ltmHttp2ProfileName,
		ltmHttp2ProfileConfigSource,
		ltmHttp2ProfileDefaultName,
		ltmHttp2ProfileInsertHeader,
		ltmHttp2ProfileInsertHeaderName,
		ltmHttp2ProfileConcurrentStreamsPerConnection,
		ltmHttp2ProfileConnectionIdleTimeout,
		ltmHttp2ProfileReceiveWindow,
		ltmHttp2ProfileFrameSize,
		ltmHttp2ProfileWriteSize,
		ltmHttp2ProfileHeaderTableSize,
		ltmHttp2ProfileEnforceTlsRequirements,
		ltmHttp2ProfileIncludeContentLength
	}
	STATUS	 current
	DESCRIPTION
		"A collection of objects of ltmHttp2Profile MIB."
	::= { bigipLocalTMGroups 174 }

ltmHttp2ProfileActivationModesGroup OBJECT-GROUP
	 OBJECTS {
		ltmHttp2ProfileActivationModesNumber,
		ltmHttp2ProfileActivationModesName,
		ltmHttp2ProfileActivationModesIndex,
		ltmHttp2ProfileActivationModesActivationModes
	}
	STATUS	 current
	DESCRIPTION
		"A collection of objects of ltmHttp2ProfileActivationModes MIB."
	::= { bigipLocalTMGroups 175 }

ltmHttp2ProfileStatGroup OBJECT-GROUP
	 OBJECTS {
		ltmHttp2ProfileStatResetStats,
		ltmHttp2ProfileStatNumber,
		ltmHttp2ProfileStatName,
		ltmHttp2ProfileStatConnectionsAccepted,
		ltmHttp2ProfileStatConnectionsCurrent,
		ltmHttp2ProfileStatConnectionsMax,
		ltmHttp2ProfileStatContinuationFramesReceived,
		ltmHttp2ProfileStatContinuationFramesSent,
		ltmHttp2ProfileStatDataFramesReceived,
		ltmHttp2ProfileStatDataFramesSent,
		ltmHttp2ProfileStatFlowsCreated,
		ltmHttp2ProfileStatFlowsCurrent,
		ltmHttp2ProfileStatFlowsMax,
		ltmHttp2ProfileStatGoawayFramesReceived,
		ltmHttp2ProfileStatGoawayFramesSent,
		ltmHttp2ProfileStatHeadersFramesReceived,
		ltmHttp2ProfileStatHeadersFramesSent,
		ltmHttp2ProfileStatHttp2RequestBytes,
		ltmHttp2ProfileStatHttp2RequestFrames,
		ltmHttp2ProfileStatHttp2ResponseBytes,
		ltmHttp2ProfileStatHttp2ResponseFrames,
		ltmHttp2ProfileStatHttpRequestBytes,
		ltmHttp2ProfileStatHttpResponseBytes,
		ltmHttp2ProfileStatPingFramesReceived,
		ltmHttp2ProfileStatPingFramesSent,
		ltmHttp2ProfileStatPriorityFramesReceived,
		ltmHttp2ProfileStatPriorityFramesSent,
		ltmHttp2ProfileStatPushPromiseFramesReceived,
		ltmHttp2ProfileStatPushPromiseFramesSent,
		ltmHttp2ProfileStatRstStreamFramesReceived,
		ltmHttp2ProfileStatRstStreamFramesSent,
		ltmHttp2ProfileStatSettingsFramesReceived,
		ltmHttp2ProfileStatSettingsFramesSent,
		ltmHttp2ProfileStatStreamsCreated,
		ltmHttp2ProfileStatStreamsCurrent,
		ltmHttp2ProfileStatStreamsMax,
		ltmHttp2ProfileStatWindowUpdateFramesReceived,
		ltmHttp2ProfileStatWindowUpdateFramesSent
	}
	STATUS	 current
	DESCRIPTION
		"A collection of objects of ltmHttp2ProfileStat MIB."
	::= { bigipLocalTMGroups 176 }

ltmLsnPoolFailureStatGroup OBJECT-GROUP
	 OBJECTS {
		ltmLsnPoolFailureStatResetStats,
		ltmLsnPoolFailureStatNumber,
		ltmLsnPoolFailureStatName,
		ltmLsnPoolFailureStatFailureCause,
		ltmLsnPoolFailureStatFailureCount
	}
	STATUS	 current
	DESCRIPTION
		"A collection of objects of ltmLsnPoolFailureStat MIB."
	::= { bigipLocalTMGroups 177 }

ltmWebsocketProfileGroup OBJECT-GROUP
	 OBJECTS {
		ltmWebsocketProfileNumber,
		ltmWebsocketProfileName,
		ltmWebsocketProfileConfigSource,
		ltmWebsocketProfileDefaultName,
		ltmWebsocketProfileMasking
	}
	STATUS	 current
	DESCRIPTION
		"A collection of objects of ltmWebsocketProfile MIB."
	::= { bigipLocalTMGroups 178 }

ltmWebsocketProfileStatGroup OBJECT-GROUP
	 OBJECTS {
		ltmWebsocketProfileStatResetStats,
		ltmWebsocketProfileStatNumber,
		ltmWebsocketProfileStatName,
		ltmWebsocketProfileStatConnectionsAccepted,
		ltmWebsocketProfileStatConnectionsCurrent,
		ltmWebsocketProfileStatConnectionsMax,
		ltmWebsocketProfileStatContFramesClientRecv,
		ltmWebsocketProfileStatContFramesServerRecv,
		ltmWebsocketProfileStatTextFramesClientRecv,
		ltmWebsocketProfileStatTextFramesServerRecv,
		ltmWebsocketProfileStatBinaryFramesClientRecv,
		ltmWebsocketProfileStatBinaryFramesServerRecv,
		ltmWebsocketProfileStatCloseFramesClientRecv,
		ltmWebsocketProfileStatCloseFramesServerRecv,
		ltmWebsocketProfileStatPingFramesClientRecv,
		ltmWebsocketProfileStatPingFramesServerRecv,
		ltmWebsocketProfileStatPongFramesClientRecv,
		ltmWebsocketProfileStatPongFramesServerRecv,
		ltmWebsocketProfileStatCloseRsnNormalClientRecv,
		ltmWebsocketProfileStatCloseRsnNormalServerRecv,
		ltmWebsocketProfileStatCloseRsnEpGoawayClientRecv,
		ltmWebsocketProfileStatCloseRsnEpGoawayServerRecv,
		ltmWebsocketProfileStatCloseRsnProtErrClientRecv,
		ltmWebsocketProfileStatCloseRsnProtErrServerRecv,
		ltmWebsocketProfileStatCloseRsnProcErrClientRecv,
		ltmWebsocketProfileStatCloseRsnProcErrServerRecv,
		ltmWebsocketProfileStatCloseRsnExtFailClientRecv,
		ltmWebsocketProfileStatCloseRsnExtFailServerRecv,
		ltmWebsocketProfileStatCloseRsnOtherClientRecv,
		ltmWebsocketProfileStatCloseRsnOtherServerRecv
	}
	STATUS	 current
	DESCRIPTION
		"A collection of objects of ltmWebsocketProfileStat MIB."
	::= { bigipLocalTMGroups 179 }

ltmTcpanalyticsProfileGroup OBJECT-GROUP
	 OBJECTS {
		ltmTcpanalyticsProfileNumber,
		ltmTcpanalyticsProfileName,
		ltmTcpanalyticsProfileConfigSource,
		ltmTcpanalyticsProfileDefaultName,
		ltmTcpanalyticsProfileCollectedByClientSide,
		ltmTcpanalyticsProfileCollectedByServerSide,
		ltmTcpanalyticsProfileCollectCity,
		ltmTcpanalyticsProfileCollectContinent,
		ltmTcpanalyticsProfileCollectCountry,
		ltmTcpanalyticsProfileCollectNexthop,
		ltmTcpanalyticsProfileCollectPostCode,
		ltmTcpanalyticsProfileCollectRegion,
		ltmTcpanalyticsProfileCollectRemoteHostIp,
		ltmTcpanalyticsProfileCollectRemoteHostSubnet,
		ltmTcpanalyticsProfileCollectedStatsInternalLogging,
		ltmTcpanalyticsProfileCollectedStatsExternalLogging,
		ltmTcpanalyticsProfileExternalLoggingPublisher
	}
	STATUS	 current
	DESCRIPTION
		"A collection of objects of ltmTcpanalyticsProfile MIB."
	::= { bigipLocalTMGroups 180 }

ltmSplitsessionclientProfileGroup OBJECT-GROUP
	 OBJECTS {
		ltmSplitsessionclientProfileNumber,
		ltmSplitsessionclientProfileName,
		ltmSplitsessionclientProfileConfigSource,
		ltmSplitsessionclientProfileDefaultName,
		ltmSplitsessionclientProfilePeerIp,
		ltmSplitsessionclientProfilePeerPort
	}
	STATUS	 current
	DESCRIPTION
		"A collection of objects of ltmSplitsessionclientProfile MIB."
	::= { bigipLocalTMGroups 181 }

ltmSplitsessionclientProfileStatGroup OBJECT-GROUP
	 OBJECTS {
		ltmSplitsessionclientProfileStatResetStats,
		ltmSplitsessionclientProfileStatNumber,
		ltmSplitsessionclientProfileStatName,
		ltmSplitsessionclientProfileStatConnectionsAccepted,
		ltmSplitsessionclientProfileStatConnectionsCurrent,
		ltmSplitsessionclientProfileStatConnectionsMax,
		ltmSplitsessionclientProfileStatConnPeerActive,
		ltmSplitsessionclientProfileStatConnPeerTimeout,
		ltmSplitsessionclientProfileStatConnPeerReset,
		ltmSplitsessionclientProfileStatPeerMsgRecd,
		ltmSplitsessionclientProfileStatPeerMsgSent
	}
	STATUS	 current
	DESCRIPTION
		"A collection of objects of ltmSplitsessionclientProfileStat MIB."
	::= { bigipLocalTMGroups 182 }

ltmSplitsessionserverProfileGroup OBJECT-GROUP
	 OBJECTS {
		ltmSplitsessionserverProfileNumber,
		ltmSplitsessionserverProfileName,
		ltmSplitsessionserverProfileConfigSource,
		ltmSplitsessionserverProfileDefaultName,
		ltmSplitsessionserverProfileListenIp,
		ltmSplitsessionserverProfileListenPort
	}
	STATUS	 current
	DESCRIPTION
		"A collection of objects of ltmSplitsessionserverProfile MIB."
	::= { bigipLocalTMGroups 183 }

ltmSplitsessionserverProfileStatGroup OBJECT-GROUP
	 OBJECTS {
		ltmSplitsessionserverProfileStatResetStats,
		ltmSplitsessionserverProfileStatNumber,
		ltmSplitsessionserverProfileStatName,
		ltmSplitsessionserverProfileStatConnectionsAccepted,
		ltmSplitsessionserverProfileStatConnectionsCurrent,
		ltmSplitsessionserverProfileStatConnectionsMax,
		ltmSplitsessionserverProfileStatConnPeerActive,
		ltmSplitsessionserverProfileStatConnPeerTimeout,
		ltmSplitsessionserverProfileStatConnPeerReset,
		ltmSplitsessionserverProfileStatPeerMsgRecd,
		ltmSplitsessionserverProfileStatPeerMsgSent
	}
	STATUS	 current
	DESCRIPTION
		"A collection of objects of ltmSplitsessionserverProfileStat MIB."
	::= { bigipLocalTMGroups 184 }

ltmHttpProxyConnectProfileGroup OBJECT-GROUP
	 OBJECTS {
		ltmHttpProxyConnectProfileNumber,
		ltmHttpProxyConnectProfileName,
		ltmHttpProxyConnectProfileConfigSource,
		ltmHttpProxyConnectProfileDefaultName,
		ltmHttpProxyConnectProfileDefaultState
	}
	STATUS	 current
	DESCRIPTION
		"A collection of objects of ltmHttpProxyConnectProfile MIB."
	::= { bigipLocalTMGroups 185 }

ltmHttpProxyConnectProfileStatGroup OBJECT-GROUP
	 OBJECTS {
		ltmHttpProxyConnectProfileStatResetStats,
		ltmHttpProxyConnectProfileStatNumber,
		ltmHttpProxyConnectProfileStatName,
		ltmHttpProxyConnectProfileStatResp2xxCnt,
		ltmHttpProxyConnectProfileStatResp3xxCnt,
		ltmHttpProxyConnectProfileStatResp4xxCnt,
		ltmHttpProxyConnectProfileStatResp5xxCnt,
		ltmHttpProxyConnectProfileStatRespOtherCnt,
		ltmHttpProxyConnectProfileStatV9Resp,
		ltmHttpProxyConnectProfileStatV10Resp,
		ltmHttpProxyConnectProfileStatV11Resp,
		ltmHttpProxyConnectProfileStatProxyConnReqs
	}
	STATUS	 current
	DESCRIPTION
		"A collection of objects of ltmHttpProxyConnectProfileStat MIB."
	::= { bigipLocalTMGroups 186 }

ltmDiametersessionProfileGroup OBJECT-GROUP
	 OBJECTS {
		ltmDiametersessionProfileNumber,
		ltmDiametersessionProfileName,
		ltmDiametersessionProfileConfigSource,
		ltmDiametersessionProfileDefaultName,
		ltmDiametersessionProfileRouteUnconfiguredPeers,
		ltmDiametersessionProfileHandshakeTimeout,
		ltmDiametersessionProfileMaxRetransmissions,
		ltmDiametersessionProfileMaxWatchdogFailures,
		ltmDiametersessionProfileResetOnTimeout,
		ltmDiametersessionProfileRetransmissionTimeout,
		ltmDiametersessionProfileRetransmissionAction,
		ltmDiametersessionProfileArrayRetransmissionErrorCode,
		ltmDiametersessionProfileRetransmissionQueueMaxMessages,
		ltmDiametersessionProfileRetransmissionQueueMaxBytes,
		ltmDiametersessionProfileRetransmissionQueueLimitHigh,
		ltmDiametersessionProfileRetransmissionQueueLimitLow,
		ltmDiametersessionProfileDiscardUnroutable,
		ltmDiametersessionProfileLoopDetection,
		ltmDiametersessionProfileWatchdogTimeout,
		ltmDiametersessionProfileMaxMessageSize,
		ltmDiametersessionProfilePersistType,
		ltmDiametersessionProfilePersistAvp,
		ltmDiametersessionProfilePersistTimeout,
		ltmDiametersessionProfileOriginHostRewrite,
		ltmDiametersessionProfileOriginRealmRewrite,
		ltmDiametersessionProfileDestHostRewrite,
		ltmDiametersessionProfileDestRealmRewrite,
		ltmDiametersessionProfileOriginHost,
		ltmDiametersessionProfileOriginRealm,
		ltmDiametersessionProfileHostIpAddress,
		ltmDiametersessionProfileVendorId,
		ltmDiametersessionProfileFirmwareRevision,
		ltmDiametersessionProfileProductName,
		ltmDiametersessionProfileAuthApplicationId,
		ltmDiametersessionProfileAcctApplicationId,
		ltmDiametersessionProfileArrayAuthApplicationId,
		ltmDiametersessionProfileArrayAcctApplicationId,
		ltmDiametersessionProfileVendorSpecificVendorId,
		ltmDiametersessionProfileVendorSpecificAuthApplicationId,
		ltmDiametersessionProfileVendorSpecificAcctApplicationId,
		ltmDiametersessionProfilePeerDelayCriticalLimit,
		ltmDiametersessionProfileEgressCriticalMessageRateLimit,
		ltmDiametersessionProfileEgressMajorMessageRateLimit,
		ltmDiametersessionProfileIngressCriticalMessageRateLimit,
		ltmDiametersessionProfileIngressMajorMessageRateLimit,
		ltmDiametersessionProfileDynamicRouteInsertion,
		ltmDiametersessionProfileDynamicRouteLookup,
		ltmDiametersessionProfileDynamicRouteTimeout,
		ltmDiametersessionProfilePeerErrorsMajorThreshold,
		ltmDiametersessionProfilePeerTimeoutsMajorThreshold,
		ltmDiametersessionProfileDisconnectPeerAction
	}
	STATUS	 current
	DESCRIPTION
		"A collection of objects of ltmDiametersessionProfile MIB."
	::= { bigipLocalTMGroups 187 }

ltmDiametersessionProfileStatGroup OBJECT-GROUP
	 OBJECTS {
		ltmDiametersessionProfileStatResetStats,
		ltmDiametersessionProfileStatNumber,
		ltmDiametersessionProfileStatName,
		ltmDiametersessionProfileStatVsName,
		ltmDiametersessionProfileStatTotCapExcReq,
		ltmDiametersessionProfileStatTotCapExcAns,
		ltmDiametersessionProfileStatTotDeviceWatchdogRequests,
		ltmDiametersessionProfileStatTotDeviceWatchdogAnswers,
		ltmDiametersessionProfileStatTotDisconnectPeerRequests,
		ltmDiametersessionProfileStatTotDisconnectPeerAnswers,
		ltmDiametersessionProfileStatTotAccountingRequests,
		ltmDiametersessionProfileStatTotAccountingAnswers,
		ltmDiametersessionProfileStatTotCreditControlRequests,
		ltmDiametersessionProfileStatTotCreditControlAnswers,
		ltmDiametersessionProfileStatTotUserAuthorizationRequests,
		ltmDiametersessionProfileStatTotUserAuthorizationAnswers,
		ltmDiametersessionProfileStatTotOtherRequests,
		ltmDiametersessionProfileStatTotOtherAnswers,
		ltmDiametersessionProfileStatTotBadMessages,
		ltmDiametersessionProfileStatTotRejectedUnconfiguredPeers,
		ltmDiametersessionProfileStatCurReqQueuedForRetrans,
		ltmDiametersessionProfileStatTotRetransReturnedBusy,
		ltmDiametersessionProfileStatTotRetransReturnedUnavail,
		ltmDiametersessionProfileStatTotRetransReqRetransmitted,
		ltmDiametersessionProfileStatTotRetransmissionTimeout,
		ltmDiametersessionProfileStatTotRetransmissionErrorCode,
		ltmDiametersessionProfileStatTotRetransmissionIrule,
		ltmDiametersessionProfileStatTotRequestReceived,
		ltmDiametersessionProfileStatTotRequestSent,
		ltmDiametersessionProfileStatTotDiscardUnroutable,
		ltmDiametersessionProfileStatTotRespondUnroutable,
		ltmDiametersessionProfileStatAveRequestLatency,
		ltmDiametersessionProfileStatAveAnswerLatency,
		ltmDiametersessionProfileStatAvePeerDelay,
		ltmDiametersessionProfileStatAveRoundTripTime,
		ltmDiametersessionProfileStatCurTrafficRate,
		ltmDiametersessionProfileStatCurErrorAnswerRatio,
		ltmDiametersessionProfileStatCurTimeoutRatio,
		ltmDiametersessionProfileStatTotResultCodeRcvd1xxx,
		ltmDiametersessionProfileStatTotResultCodeRcvd2xxx,
		ltmDiametersessionProfileStatTotResultCodeRcvd3xxx,
		ltmDiametersessionProfileStatTotResultCodeRcvd4xxx,
		ltmDiametersessionProfileStatTotResultCodeRcvd5xxx,
		ltmDiametersessionProfileStatTotResultCodeSent1xxx,
		ltmDiametersessionProfileStatTotResultCodeSent2xxx,
		ltmDiametersessionProfileStatTotResultCodeSent3xxx,
		ltmDiametersessionProfileStatTotResultCodeSent4xxx,
		ltmDiametersessionProfileStatTotResultCodeSent5xxx,
		ltmDiametersessionProfileStatTotLoopedRequests
	}
	STATUS	 current
	DESCRIPTION
		"A collection of objects of ltmDiametersessionProfileStat MIB."
	::= { bigipLocalTMGroups 188 }

ltmDiameterrouterProfileGroup OBJECT-GROUP
	 OBJECTS {
		ltmDiameterrouterProfileNumber,
		ltmDiameterrouterProfileName,
		ltmDiameterrouterProfileConfigSource,
		ltmDiameterrouterProfileDefaultName,
		ltmDiameterrouterProfileMirrored,
		ltmDiameterrouterProfileTrafficGroup,
		ltmDiameterrouterProfileSupportedApplications,
		ltmDiameterrouterProfileIgnorePeerPort,
		ltmDiameterrouterProfileMaxPendingMessages,
		ltmDiameterrouterProfileMaxPendingBytes,
		ltmDiameterrouterProfileHaMsgSweeperInterval,
		ltmDiameterrouterProfilePendingReqSweeperInterval,
		ltmDiameterrouterProfileUseLocalConnection,
		ltmDiameterrouterProfileTransactionTimeout,
		ltmDiameterrouterProfileMaxRetries,
		ltmDiameterrouterProfileIruleScopeMessage,
		ltmDiameterrouterProfilePerPeerStats,
		ltmDiameterrouterProfileAssociateClientsideToPmbr
	}
	STATUS	 current
	DESCRIPTION
		"A collection of objects of ltmDiameterrouterProfile MIB."
	::= { bigipLocalTMGroups 189 }

ltmDiameterrouterProfileStatGroup OBJECT-GROUP
	 OBJECTS {
		ltmDiameterrouterProfileStatResetStats,
		ltmDiameterrouterProfileStatNumber,
		ltmDiameterrouterProfileStatName,
		ltmDiameterrouterProfileStatVsName,
		ltmDiameterrouterProfileStatTotMessgesIn,
		ltmDiameterrouterProfileStatTotMessagesInRetry,
		ltmDiameterrouterProfileStatTotMessagesOut,
		ltmDiameterrouterProfileStatTotMessagesCannotReturn,
		ltmDiameterrouterProfileStatTotMessagesRouted,
		ltmDiameterrouterProfileStatTotMessagesUnroutable,
		ltmDiameterrouterProfileStatTotMessagesDropped,
		ltmDiameterrouterProfileStatTotMessagesQueueFull,
		ltmDiameterrouterProfileStatTotMessagesNoConnection,
		ltmDiameterrouterProfileStatTotMessagesConnectionClosed,
		ltmDiameterrouterProfileStatTotMessagesInternalError,
		ltmDiameterrouterProfileStatTotMessagesPersistInUse,
		ltmDiameterrouterProfileStatTotMessagesStandbyDropped,
		ltmDiameterrouterProfileStatTotMessagesMaxRetries,
		ltmDiameterrouterProfileStatTotMessagesInCloned,
		ltmDiameterrouterProfileStatTotMessagesReturned,
		ltmDiameterrouterProfileStatTotPayloadBytesIn,
		ltmDiameterrouterProfileStatTotPayloadBytesOut,
		ltmDiameterrouterProfileStatCurIncomingStreams,
		ltmDiameterrouterProfileStatCurOutgoingStreams,
		ltmDiameterrouterProfileStatTotIncomingStreams,
		ltmDiameterrouterProfileStatTotOutgoingStreams,
		ltmDiameterrouterProfileStatTotFailedOutgoingStreams,
		ltmDiameterrouterProfileStatCurIncomingConnections,
		ltmDiameterrouterProfileStatCurOutgoingConnections,
		ltmDiameterrouterProfileStatCurAutoInitOutgoingConns,
		ltmDiameterrouterProfileStatTotIncomingConnections,
		ltmDiameterrouterProfileStatTotOutgoingConnections,
		ltmDiameterrouterProfileStatTotAutoInitOutgoingConns,
		ltmDiameterrouterProfileStatTotFailedOutgoingConnections,
		ltmDiameterrouterProfileStatTotFailAutoInitOutgoingConns,
		ltmDiameterrouterProfileStatCurPassthruConnections,
		ltmDiameterrouterProfileStatTotPassthruConnections,
		ltmDiameterrouterProfileStatTotFailedPassthruConnections,
		ltmDiameterrouterProfileStatTotPassthruBytes,
		ltmDiameterrouterProfileStatCurPendingRequests,
		ltmDiameterrouterProfileStatTotExpiredPendingRequests,
		ltmDiameterrouterProfileStatTotDroppedUnexpectedAnswers,
		ltmDiameterrouterProfileStatTotDroppedLateAnswers,
		ltmDiameterrouterProfileStatCurDynamicRoutes
	}
	STATUS	 current
	DESCRIPTION
		"A collection of objects of ltmDiameterrouterProfileStat MIB."
	::= { bigipLocalTMGroups 190 }

ltmMrPmbrDiameterSessionStatGroup OBJECT-GROUP
	 OBJECTS {
		ltmMrPmbrDiameterSessionStatResetStats,
		ltmMrPmbrDiameterSessionStatNumber,
		ltmMrPmbrDiameterSessionStatRouterInst,
		ltmMrPmbrDiameterSessionStatMrType,
		ltmMrPmbrDiameterSessionStatTrName,
		ltmMrPmbrDiameterSessionStatPool,
		ltmMrPmbrDiameterSessionStatAddrType,
		ltmMrPmbrDiameterSessionStatAddr,
		ltmMrPmbrDiameterSessionStatProfileName,
		ltmMrPmbrDiameterSessionStatPort,
		ltmMrPmbrDiameterSessionStatTotCapExcReq,
		ltmMrPmbrDiameterSessionStatTotCapExcAns,
		ltmMrPmbrDiameterSessionStatTotDeviceWatchdogRequests,
		ltmMrPmbrDiameterSessionStatTotDeviceWatchdogAnswers,
		ltmMrPmbrDiameterSessionStatTotDisconnectPeerRequests,
		ltmMrPmbrDiameterSessionStatTotDisconnectPeerAnswers,
		ltmMrPmbrDiameterSessionStatTotAccountingRequests,
		ltmMrPmbrDiameterSessionStatTotAccountingAnswers,
		ltmMrPmbrDiameterSessionStatTotCreditControlRequests,
		ltmMrPmbrDiameterSessionStatTotCreditControlAnswers,
		ltmMrPmbrDiameterSessionStatTotUserAuthorizationRequests,
		ltmMrPmbrDiameterSessionStatTotUserAuthorizationAnswers,
		ltmMrPmbrDiameterSessionStatTotOtherRequests,
		ltmMrPmbrDiameterSessionStatTotOtherAnswers,
		ltmMrPmbrDiameterSessionStatTotBadMessages,
		ltmMrPmbrDiameterSessionStatTotRejectedUnconfiguredPeers,
		ltmMrPmbrDiameterSessionStatCurReqQueuedForRetrans,
		ltmMrPmbrDiameterSessionStatTotRetransReturnedBusy,
		ltmMrPmbrDiameterSessionStatTotRetransReturnedUnavail,
		ltmMrPmbrDiameterSessionStatTotRetransReqRetransmit,
		ltmMrPmbrDiameterSessionStatTotRetransmissionTimeout,
		ltmMrPmbrDiameterSessionStatTotRetransmissionErrorCode,
		ltmMrPmbrDiameterSessionStatTotRetransmissionIrule,
		ltmMrPmbrDiameterSessionStatTotRequestReceived,
		ltmMrPmbrDiameterSessionStatTotRequestSent,
		ltmMrPmbrDiameterSessionStatTotDiscardUnroutable,
		ltmMrPmbrDiameterSessionStatTotRespondUnroutable,
		ltmMrPmbrDiameterSessionStatAveRequestLatency,
		ltmMrPmbrDiameterSessionStatAveAnswerLatency,
		ltmMrPmbrDiameterSessionStatAvePeerDelay,
		ltmMrPmbrDiameterSessionStatAveRoundTripTime,
		ltmMrPmbrDiameterSessionStatCurTrafficRate,
		ltmMrPmbrDiameterSessionStatCurTimeoutRatio,
		ltmMrPmbrDiameterSessionStatCurErrorAnswerRatio,
		ltmMrPmbrDiameterSessionStatTotResultCodeRcvd1xxx,
		ltmMrPmbrDiameterSessionStatTotResultCodeRcvd2xxx,
		ltmMrPmbrDiameterSessionStatTotResultCodeRcvd3xxx,
		ltmMrPmbrDiameterSessionStatTotResultCodeRcvd4xxx,
		ltmMrPmbrDiameterSessionStatTotResultCodeRcvd5xxx,
		ltmMrPmbrDiameterSessionStatTotResultCodeSent1xxx,
		ltmMrPmbrDiameterSessionStatTotResultCodeSent2xxx,
		ltmMrPmbrDiameterSessionStatTotResultCodeSent3xxx,
		ltmMrPmbrDiameterSessionStatTotResultCodeSent4xxx,
		ltmMrPmbrDiameterSessionStatTotResultCodeSent5xxx
	}
	STATUS	 current
	DESCRIPTION
		"A collection of objects of ltmMrPmbrDiameterSessionStat MIB."
	::= { bigipLocalTMGroups 191 }

ltmMrPmbrDiameterRouterStatGroup OBJECT-GROUP
	 OBJECTS {
		ltmMrPmbrDiameterRouterStatResetStats,
		ltmMrPmbrDiameterRouterStatNumber,
		ltmMrPmbrDiameterRouterStatRouterInst,
		ltmMrPmbrDiameterRouterStatMrType,
		ltmMrPmbrDiameterRouterStatTrName,
		ltmMrPmbrDiameterRouterStatPool,
		ltmMrPmbrDiameterRouterStatAddrType,
		ltmMrPmbrDiameterRouterStatAddr,
		ltmMrPmbrDiameterRouterStatPort,
		ltmMrPmbrDiameterRouterStatTotMessgesIn,
		ltmMrPmbrDiameterRouterStatTotMessagesInRetry,
		ltmMrPmbrDiameterRouterStatTotMessagesOut,
		ltmMrPmbrDiameterRouterStatTotMessagesCannotReturn,
		ltmMrPmbrDiameterRouterStatTotMessagesRouted,
		ltmMrPmbrDiameterRouterStatTotMessagesUnroutable,
		ltmMrPmbrDiameterRouterStatTotMessagesDropped,
		ltmMrPmbrDiameterRouterStatTotMessagesQueueFull,
		ltmMrPmbrDiameterRouterStatTotMessagesNoConnection,
		ltmMrPmbrDiameterRouterStatTotMessagesConnectionClosed,
		ltmMrPmbrDiameterRouterStatTotMessagesInternalError,
		ltmMrPmbrDiameterRouterStatTotMessagesPersistInUse,
		ltmMrPmbrDiameterRouterStatTotMessagesStandbyDropped,
		ltmMrPmbrDiameterRouterStatTotMessagesMaxRetries,
		ltmMrPmbrDiameterRouterStatTotMessagesInCloned,
		ltmMrPmbrDiameterRouterStatTotMessagesReturned,
		ltmMrPmbrDiameterRouterStatTotPayloadBytesIn,
		ltmMrPmbrDiameterRouterStatTotPayloadBytesOut,
		ltmMrPmbrDiameterRouterStatCurIncomingStreams,
		ltmMrPmbrDiameterRouterStatCurOutgoingStreams,
		ltmMrPmbrDiameterRouterStatTotIncomingStreams,
		ltmMrPmbrDiameterRouterStatTotOutgoingStreams,
		ltmMrPmbrDiameterRouterStatTotFailedOutgoingStreams,
		ltmMrPmbrDiameterRouterStatCurIncomingConnections,
		ltmMrPmbrDiameterRouterStatCurOutgoingConnections,
		ltmMrPmbrDiameterRouterStatCurAutoInitOutgoingConns,
		ltmMrPmbrDiameterRouterStatTotIncomingConnections,
		ltmMrPmbrDiameterRouterStatTotOutgoingConnections,
		ltmMrPmbrDiameterRouterStatTotAutoInitOutgoingConns,
		ltmMrPmbrDiameterRouterStatTotFailedOutgoingConnections,
		ltmMrPmbrDiameterRouterStatTotFailAutoInitOutgoingConns,
		ltmMrPmbrDiameterRouterStatCurPassthruConnections,
		ltmMrPmbrDiameterRouterStatTotPassthruConnections,
		ltmMrPmbrDiameterRouterStatTotFailedPassthruConnections,
		ltmMrPmbrDiameterRouterStatTotPassthruBytes,
		ltmMrPmbrDiameterRouterStatCurPendingRequests,
		ltmMrPmbrDiameterRouterStatTotExpiredPendingRequests,
		ltmMrPmbrDiameterRouterStatTotDroppedUnexpectedAnswers,
		ltmMrPmbrDiameterRouterStatTotDroppedLateAnswers
	}
	STATUS	 current
	DESCRIPTION
		"A collection of objects of ltmMrPmbrDiameterRouterStat MIB."
	::= { bigipLocalTMGroups 192 }

ltmSipsessionProfileStatGroup OBJECT-GROUP
	 OBJECTS {
		ltmSipsessionProfileStatResetStats,
		ltmSipsessionProfileStatNumber,
		ltmSipsessionProfileStatName,
		ltmSipsessionProfileStatVsName,
		ltmSipsessionProfileStatRequests,
		ltmSipsessionProfileStatResponses,
		ltmSipsessionProfileStatBadmsgs,
		ltmSipsessionProfileStatBadmsgsReq,
		ltmSipsessionProfileStatDrops,
		ltmSipsessionProfileStatDropsReq,
		ltmSipsessionProfileStatInvite,
		ltmSipsessionProfileStatAck,
		ltmSipsessionProfileStatBye,
		ltmSipsessionProfileStatCancel,
		ltmSipsessionProfileStatOptions,
		ltmSipsessionProfileStatRegisterReq,
		ltmSipsessionProfileStatPrack,
		ltmSipsessionProfileStatSubscribe,
		ltmSipsessionProfileStatNotify,
		ltmSipsessionProfileStatPublish,
		ltmSipsessionProfileStatInfo,
		ltmSipsessionProfileStatRefer,
		ltmSipsessionProfileStatMessage,
		ltmSipsessionProfileStatUpdateReq,
		ltmSipsessionProfileStatService,
		ltmSipsessionProfileStatBenotify,
		ltmSipsessionProfileStatNegotiate,
		ltmSipsessionProfileStatOther,
		ltmSipsessionProfileStatProvisional,
		ltmSipsessionProfileStatSuccessful,
		ltmSipsessionProfileStatRedirection,
		ltmSipsessionProfileStatClientFailures,
		ltmSipsessionProfileStatServerFailures,
		ltmSipsessionProfileStatGlobalFailures,
		ltmSipsessionProfileStatBadRequest,
		ltmSipsessionProfileStatBadRequest400Sent,
		ltmSipsessionProfileStatNotFound,
		ltmSipsessionProfileStatNotFound404Sent,
		ltmSipsessionProfileStatRequestEntityTooLarge,
		ltmSipsessionProfileStatRequestEntityTooLarge413Sent,
		ltmSipsessionProfileStatUnsupportedUriScheme,
		ltmSipsessionProfileStatUnsupportedUriScheme416Sent,
		ltmSipsessionProfileStatTemporarilyUnavailable,
		ltmSipsessionProfileStatTemporarilyUnavailable480Sent,
		ltmSipsessionProfileStatTransactionDoesNotExist,
		ltmSipsessionProfileStatTransactionDoesNotExist481Sent,
		ltmSipsessionProfileStatLoopDetected,
		ltmSipsessionProfileStatLoopDetected482Sent,
		ltmSipsessionProfileStatTooManyHops,
		ltmSipsessionProfileStatTooManyHops483Sent,
		ltmSipsessionProfileStatAddressIncomplete,
		ltmSipsessionProfileStatAddressIncomplete484Sent,
		ltmSipsessionProfileStatNotAcceptableHere,
		ltmSipsessionProfileStatNotAcceptableHere488Sent,
		ltmSipsessionProfileStatServerInternalError,
		ltmSipsessionProfileStatServerInternalError500Sent,
		ltmSipsessionProfileStatNotImplemented,
		ltmSipsessionProfileStatNotImplemented501Sent,
		ltmSipsessionProfileStatServiceUnavailable,
		ltmSipsessionProfileStatServiceUnavailable503Sent,
		ltmSipsessionProfileStatVersionNotSupported,
		ltmSipsessionProfileStatVersionNotSupported505Sent
	}
	STATUS	 current
	DESCRIPTION
		"A collection of objects of ltmSipsessionProfileStat MIB."
	::= { bigipLocalTMGroups 193 }

ltmSiprouterProfileStatGroup OBJECT-GROUP
	 OBJECTS {
		ltmSiprouterProfileStatResetStats,
		ltmSiprouterProfileStatNumber,
		ltmSiprouterProfileStatName,
		ltmSiprouterProfileStatVsName,
		ltmSiprouterProfileStatTotMessgesIn,
		ltmSiprouterProfileStatTotMessagesInRetry,
		ltmSiprouterProfileStatTotMessagesOut,
		ltmSiprouterProfileStatTotMessagesCannotReturn,
		ltmSiprouterProfileStatTotMessagesRouted,
		ltmSiprouterProfileStatTotMessagesUnroutable,
		ltmSiprouterProfileStatTotMessagesDropped,
		ltmSiprouterProfileStatTotMessagesQueueFull,
		ltmSiprouterProfileStatTotMessagesNoConnection,
		ltmSiprouterProfileStatTotMessagesConnectionClosed,
		ltmSiprouterProfileStatTotMessagesInternalError,
		ltmSiprouterProfileStatTotMessagesPersistInUse,
		ltmSiprouterProfileStatTotMessagesStandbyDropped,
		ltmSiprouterProfileStatTotMessagesMaxRetries,
		ltmSiprouterProfileStatTotMessagesInCloned,
		ltmSiprouterProfileStatTotMessagesReturned,
		ltmSiprouterProfileStatTotPayloadBytesIn,
		ltmSiprouterProfileStatTotPayloadBytesOut,
		ltmSiprouterProfileStatCurIncomingStreams,
		ltmSiprouterProfileStatCurOutgoingStreams,
		ltmSiprouterProfileStatTotIncomingStreams,
		ltmSiprouterProfileStatTotOutgoingStreams,
		ltmSiprouterProfileStatTotFailedOutgoingStreams,
		ltmSiprouterProfileStatCurIncomingConnections,
		ltmSiprouterProfileStatCurOutgoingConnections,
		ltmSiprouterProfileStatCurAutoInitOutgoingConns,
		ltmSiprouterProfileStatTotIncomingConnections,
		ltmSiprouterProfileStatTotOutgoingConnections,
		ltmSiprouterProfileStatTotAutoInitOutgoingConns,
		ltmSiprouterProfileStatTotFailedOutgoingConnections,
		ltmSiprouterProfileStatTotFailAutoInitOutgoingConns,
		ltmSiprouterProfileStatCurPassthruConnections,
		ltmSiprouterProfileStatTotPassthruConnections,
		ltmSiprouterProfileStatTotFailedPassthruConnections,
		ltmSiprouterProfileStatTotPassthruBytes,
		ltmSiprouterProfileStatCurrPendingCalls,
		ltmSiprouterProfileStatCurrActiveCalls,
		ltmSiprouterProfileStatTotSuccessfulCalls,
		ltmSiprouterProfileStatTotRejectedCalls,
		ltmSiprouterProfileStatTotCancelledCalls,
		ltmSiprouterProfileStatActiveRegistrations,
		ltmSiprouterProfileStatRejectedRegistrations
	}
	STATUS	 current
	DESCRIPTION
		"A collection of objects of ltmSiprouterProfileStat MIB."
	::= { bigipLocalTMGroups 194 }

ltmMrPmbrSipSessionStatGroup OBJECT-GROUP
	 OBJECTS {
		ltmMrPmbrSipSessionStatResetStats,
		ltmMrPmbrSipSessionStatNumber,
		ltmMrPmbrSipSessionStatRouterInst,
		ltmMrPmbrSipSessionStatMrType,
		ltmMrPmbrSipSessionStatTrName,
		ltmMrPmbrSipSessionStatPool,
		ltmMrPmbrSipSessionStatProfileName,
		ltmMrPmbrSipSessionStatAddrType,
		ltmMrPmbrSipSessionStatAddr,
		ltmMrPmbrSipSessionStatPort,
		ltmMrPmbrSipSessionStatRequests,
		ltmMrPmbrSipSessionStatResponses,
		ltmMrPmbrSipSessionStatBadmsgs,
		ltmMrPmbrSipSessionStatBadmsgsReq,
		ltmMrPmbrSipSessionStatDrops,
		ltmMrPmbrSipSessionStatDropsReq,
		ltmMrPmbrSipSessionStatInvite,
		ltmMrPmbrSipSessionStatAck,
		ltmMrPmbrSipSessionStatBye,
		ltmMrPmbrSipSessionStatCancel,
		ltmMrPmbrSipSessionStatOptions,
		ltmMrPmbrSipSessionStatRegisterReq,
		ltmMrPmbrSipSessionStatPrack,
		ltmMrPmbrSipSessionStatSubscribe,
		ltmMrPmbrSipSessionStatNotify,
		ltmMrPmbrSipSessionStatPublish,
		ltmMrPmbrSipSessionStatInfo,
		ltmMrPmbrSipSessionStatRefer,
		ltmMrPmbrSipSessionStatMessage,
		ltmMrPmbrSipSessionStatUpdateReq,
		ltmMrPmbrSipSessionStatService,
		ltmMrPmbrSipSessionStatBenotify,
		ltmMrPmbrSipSessionStatNegotiate,
		ltmMrPmbrSipSessionStatOther,
		ltmMrPmbrSipSessionStatProvisional,
		ltmMrPmbrSipSessionStatSuccessful,
		ltmMrPmbrSipSessionStatRedirection,
		ltmMrPmbrSipSessionStatClientFailures,
		ltmMrPmbrSipSessionStatServerFailures,
		ltmMrPmbrSipSessionStatGlobalFailures,
		ltmMrPmbrSipSessionStatBadRequest,
		ltmMrPmbrSipSessionStatBadRequest400Sent,
		ltmMrPmbrSipSessionStatNotFound,
		ltmMrPmbrSipSessionStatNotFound404Sent,
		ltmMrPmbrSipSessionStatRequestEntityTooLarge,
		ltmMrPmbrSipSessionStatRequestEntityTooLarge413Sent,
		ltmMrPmbrSipSessionStatUnsupportedUriScheme,
		ltmMrPmbrSipSessionStatUnsupportedUriScheme416Sent,
		ltmMrPmbrSipSessionStatTemporarilyUnavailable,
		ltmMrPmbrSipSessionStatTemporarilyUnavailable480Sent,
		ltmMrPmbrSipSessionStatTransactionDoesNotExist,
		ltmMrPmbrSipSessionStatTransactionDoesNotExist481Sent,
		ltmMrPmbrSipSessionStatLoopDetected,
		ltmMrPmbrSipSessionStatLoopDetected482Sent,
		ltmMrPmbrSipSessionStatTooManyHops,
		ltmMrPmbrSipSessionStatTooManyHops483Sent,
		ltmMrPmbrSipSessionStatAddressIncomplete,
		ltmMrPmbrSipSessionStatAddressIncomplete484Sent,
		ltmMrPmbrSipSessionStatNotAcceptableHere,
		ltmMrPmbrSipSessionStatNotAcceptableHere488Sent,
		ltmMrPmbrSipSessionStatServerInternalError,
		ltmMrPmbrSipSessionStatServerInternalError500Sent,
		ltmMrPmbrSipSessionStatNotImplemented,
		ltmMrPmbrSipSessionStatNotImplemented501Sent,
		ltmMrPmbrSipSessionStatServiceUnavailable,
		ltmMrPmbrSipSessionStatServiceUnavailable503Sent,
		ltmMrPmbrSipSessionStatVersionNotSupported,
		ltmMrPmbrSipSessionStatVersionNotSupported505Sent
	}
	STATUS	 current
	DESCRIPTION
		"A collection of objects of ltmMrPmbrSipSessionStat MIB."
	::= { bigipLocalTMGroups 195 }

ltmMrPmbrSipRouterStatGroup OBJECT-GROUP
	 OBJECTS {
		ltmMrPmbrSipRouterStatResetStats,
		ltmMrPmbrSipRouterStatNumber,
		ltmMrPmbrSipRouterStatRouterInst,
		ltmMrPmbrSipRouterStatMrType,
		ltmMrPmbrSipRouterStatTrName,
		ltmMrPmbrSipRouterStatPool,
		ltmMrPmbrSipRouterStatAddrType,
		ltmMrPmbrSipRouterStatAddr,
		ltmMrPmbrSipRouterStatPort,
		ltmMrPmbrSipRouterStatTotMessgesIn,
		ltmMrPmbrSipRouterStatTotMessagesInRetry,
		ltmMrPmbrSipRouterStatTotMessagesOut,
		ltmMrPmbrSipRouterStatTotMessagesCannotReturn,
		ltmMrPmbrSipRouterStatTotMessagesRouted,
		ltmMrPmbrSipRouterStatTotMessagesUnroutable,
		ltmMrPmbrSipRouterStatTotMessagesDropped,
		ltmMrPmbrSipRouterStatTotMessagesQueueFull,
		ltmMrPmbrSipRouterStatTotMessagesNoConnection,
		ltmMrPmbrSipRouterStatTotMessagesConnectionClosed,
		ltmMrPmbrSipRouterStatTotMessagesInternalError,
		ltmMrPmbrSipRouterStatTotMessagesPersistInUse,
		ltmMrPmbrSipRouterStatTotMessagesStandbyDropped,
		ltmMrPmbrSipRouterStatTotMessagesMaxRetries,
		ltmMrPmbrSipRouterStatTotMessagesInCloned,
		ltmMrPmbrSipRouterStatTotMessagesReturned,
		ltmMrPmbrSipRouterStatTotPayloadBytesIn,
		ltmMrPmbrSipRouterStatTotPayloadBytesOut,
		ltmMrPmbrSipRouterStatCurIncomingStreams,
		ltmMrPmbrSipRouterStatCurOutgoingStreams,
		ltmMrPmbrSipRouterStatTotIncomingStreams,
		ltmMrPmbrSipRouterStatTotOutgoingStreams,
		ltmMrPmbrSipRouterStatTotFailedOutgoingStreams,
		ltmMrPmbrSipRouterStatCurIncomingConnections,
		ltmMrPmbrSipRouterStatCurOutgoingConnections,
		ltmMrPmbrSipRouterStatCurAutoInitOutgoingConns,
		ltmMrPmbrSipRouterStatTotIncomingConnections,
		ltmMrPmbrSipRouterStatTotOutgoingConnections,
		ltmMrPmbrSipRouterStatTotAutoInitOutgoingConns,
		ltmMrPmbrSipRouterStatTotFailedOutgoingConnections,
		ltmMrPmbrSipRouterStatTotFailAutoInitOutgoingConns,
		ltmMrPmbrSipRouterStatCurPassthruConnections,
		ltmMrPmbrSipRouterStatTotPassthruConnections,
		ltmMrPmbrSipRouterStatTotFailedPassthruConnections,
		ltmMrPmbrSipRouterStatTotPassthruBytes,
		ltmMrPmbrSipRouterStatCurrPendingCalls,
		ltmMrPmbrSipRouterStatCurrActiveCalls,
		ltmMrPmbrSipRouterStatTotSuccessfulCalls,
		ltmMrPmbrSipRouterStatTotRejectedCalls,
		ltmMrPmbrSipRouterStatTotCancelledCalls,
		ltmMrPmbrSipRouterStatActiveRegistrations,
		ltmMrPmbrSipRouterStatRejectedRegistrations,
		ltmMrPmbrSipRouterStatMaxRegistrationsPerSubscriber,
		ltmMrPmbrSipRouterStatConcurrentSessionsPerSubscriber
	}
	STATUS	 current
	DESCRIPTION
		"A collection of objects of ltmMrPmbrSipRouterStat MIB."
	::= { bigipLocalTMGroups 196 }

ltmServerSslProfileC3dCertExtensionCustomOidsGroup OBJECT-GROUP
	 OBJECTS {
		ltmServerSslProfileC3dCertExtensionCustomOidsNumber,
		ltmServerSslProfileC3dCertExtensionCustomOidsServerssl,
		ltmServerSslProfileC3dCertExtensionCustomOidsIndex,
		ltmServerSslProfileC3dCertExtensionCustomOidsOid
	}
	STATUS	 current
	DESCRIPTION
		"A collection of objects of ltmServerSslProfileC3dCertExtensionCustomOids MIB."
	::= { bigipLocalTMGroups 197 }

ltmFwNatDynamicPoolGroup OBJECT-GROUP
	 OBJECTS {
		ltmFwNatDynamicPoolNumber,
		ltmFwNatDynamicPoolName,
		ltmFwNatDynamicPoolDescription,
		ltmFwNatDynamicPoolAddressCount,
		ltmFwNatDynamicPoolPortCount,
		ltmFwNatDynamicPoolAddrFamily,
		ltmFwNatDynamicPoolType,
		ltmFwNatDynamicPoolPatMode,
		ltmFwNatDynamicPoolInboundMode,
		ltmFwNatDynamicPoolMappingMode,
		ltmFwNatDynamicPoolMappingTimeout,
		ltmFwNatDynamicPoolBlockLifetime,
		ltmFwNatDynamicPoolBlockIdleTimeout,
		ltmFwNatDynamicPoolZombieTimeout,
		ltmFwNatDynamicPoolBlockSize,
		ltmFwNatDynamicPoolClientBlockLimit,
		ltmFwNatDynamicPoolRouteAdvertisement,
		ltmFwNatDynamicPoolProxyArp,
		ltmFwNatDynamicPoolHairpinMode,
		ltmFwNatDynamicPoolIcmpEcho,
		ltmFwNatDynamicPoolClientConnectionLimit,
		ltmFwNatDynamicPoolEgressInterfacesEnabled,
		ltmFwNatDynamicPoolTrafficGroup,
		ltmFwNatDynamicPoolPcpName,
		ltmFwNatDynamicPoolPcpSelfipName,
		ltmFwNatDynamicPoolDsliteTunnel,
		ltmFwNatDynamicPoolPcpEpoch
	}
	STATUS	 current
	DESCRIPTION
		"A collection of objects of ltmFwNatDynamicPool MIB."
	::= { bigipLocalTMGroups 198 }

ltmFwNatDynamicPoolStatGroup OBJECT-GROUP
	 OBJECTS {
		ltmFwNatDynamicPoolStatResetStats,
		ltmFwNatDynamicPoolStatNumber,
		ltmFwNatDynamicPoolStatName,
		ltmFwNatDynamicPoolStatLsnTranslationRequests,
		ltmFwNatDynamicPoolStatLsnHairpinConnectionRequests,
		ltmFwNatDynamicPoolStatLsnActiveTranslations,
		ltmFwNatDynamicPoolStatLsnActiveHairpinConnections,
		ltmFwNatDynamicPoolStatLsnTranslationRequestFailures,
		ltmFwNatDynamicPoolStatLsnPersistenceMappingFailures,
		ltmFwNatDynamicPoolStatLsnHairpinConnectionFailures,
		ltmFwNatDynamicPoolStatLsnBackupPoolTranslations,
		ltmFwNatDynamicPoolStatLsnActiveEndPoints,
		ltmFwNatDynamicPoolStatLsnEndPoints,
		ltmFwNatDynamicPoolStatLsnEndPointsHighValue,
		ltmFwNatDynamicPoolStatPbaActivePortBlocks,
		ltmFwNatDynamicPoolStatPbaActiveClientsReachedLimit,
		ltmFwNatDynamicPoolStatPbaActiveZombiePortBlocks,
		ltmFwNatDynamicPoolStatPbaPortBlockAllocations,
		ltmFwNatDynamicPoolStatPbaPortBlockAllocationFailures,
		ltmFwNatDynamicPoolStatPbaPortBlockDeallocations,
		ltmFwNatDynamicPoolStatPbaClientsReachedLimit,
		ltmFwNatDynamicPoolStatPbaZombiePortBlocksCreated,
		ltmFwNatDynamicPoolStatPbaZombiePortBlocksDeleted,
		ltmFwNatDynamicPoolStatPbaZombiePortBlockConnsKilled,
		ltmFwNatDynamicPoolStatPcpAnnounceRequests,
		ltmFwNatDynamicPoolStatPcpAnnounceResponsesUcast,
		ltmFwNatDynamicPoolStatPcpAnnounceResponsesMulticast,
		ltmFwNatDynamicPoolStatPcpMapRequests,
		ltmFwNatDynamicPoolStatPcpMapResponses,
		ltmFwNatDynamicPoolStatPcpPeerRequests,
		ltmFwNatDynamicPoolStatPcpPeerResponses,
		ltmFwNatDynamicPoolStatPcpErrorsInvalidRequest,
		ltmFwNatDynamicPoolStatPcpErrorsUnavailableResource,
		ltmFwNatDynamicPoolStatPcpErrorsNotAuthorized,
		ltmFwNatDynamicPoolStatPcpErrorsOther,
		ltmFwNatDynamicPoolStatPbaTotalPortBlocks,
		ltmFwNatDynamicPoolStatPbaPercentFreePortBlocksSnmp
	}
	STATUS	 current
	DESCRIPTION
		"A collection of objects of ltmFwNatDynamicPoolStat MIB."
	::= { bigipLocalTMGroups 199 }

ltmFwNatDynamicPoolFailureStatGroup OBJECT-GROUP
	 OBJECTS {
		ltmFwNatDynamicPoolFailureStatResetStats,
		ltmFwNatDynamicPoolFailureStatNumber,
		ltmFwNatDynamicPoolFailureStatName,
		ltmFwNatDynamicPoolFailureStatFailureCause,
		ltmFwNatDynamicPoolFailureStatFailureCount
	}
	STATUS	 current
	DESCRIPTION
		"A collection of objects of ltmFwNatDynamicPoolFailureStat MIB."
	::= { bigipLocalTMGroups 200 }

ltmFwNatStaticDestinationTranslationPoolGroup OBJECT-GROUP
	 OBJECTS {
		ltmFwNatStaticDestinationTranslationPoolNumber,
		ltmFwNatStaticDestinationTranslationPoolName,
		ltmFwNatStaticDestinationTranslationPoolDescription,
		ltmFwNatStaticDestinationTranslationPoolType,
		ltmFwNatStaticDestinationTranslationPoolPortCount
	}
	STATUS	 current
	DESCRIPTION
		"A collection of objects of ltmFwNatStaticDestinationTranslationPool MIB."
	::= { bigipLocalTMGroups 201 }

ltmFwNatStaticDestinationTranslationPoolStatGroup OBJECT-GROUP
	 OBJECTS {
		ltmFwNatStaticDestinationTranslationPoolStatResetStats,
		ltmFwNatStaticDestinationTranslationPoolStatNumber,
		ltmFwNatStaticDestinationTranslationPoolStatName,
		ltmFwNatStaticDestinationTranslationPoolStatTransReqs,
		ltmFwNatStaticDestinationTranslationPoolStatTransReqFails,
		ltmFwNatStaticDestinationTranslationPoolStatBidirReqs,
		ltmFwNatStaticDestinationTranslationPoolStatBidirReqFails,
		ltmFwNatStaticDestinationTranslationPoolStatErrAddrTrans,
		ltmFwNatStaticDestinationTranslationPoolStatErrPortTrans,
		ltmFwNatStaticDestinationTranslationPoolStatErrFlowCollis,
		ltmFwNatStaticDestinationTranslationPoolStatErrCfgMismtch,
		ltmFwNatStaticDestinationTranslationPoolStatErrMemory,
		ltmFwNatStaticDestinationTranslationPoolStatSubscrIdLkps,
		ltmFwNatStaticDestinationTranslationPoolStatSubscrIdNotFd,
		ltmFwNatStaticDestinationTranslationPoolStatSubscrIdErrs
	}
	STATUS	 current
	DESCRIPTION
		"A collection of objects of ltmFwNatStaticDestinationTranslationPoolStat MIB."
	::= { bigipLocalTMGroups 202 }

ltmFwNatStaticSourceTranslationPoolGroup OBJECT-GROUP
	 OBJECTS {
		ltmFwNatStaticSourceTranslationPoolNumber,
		ltmFwNatStaticSourceTranslationPoolName,
		ltmFwNatStaticSourceTranslationPoolDescription,
		ltmFwNatStaticSourceTranslationPoolPortCount,
		ltmFwNatStaticSourceTranslationPoolType,
		ltmFwNatStaticSourceTranslationPoolRouteAdvertisement,
		ltmFwNatStaticSourceTranslationPoolProxyArp,
		ltmFwNatStaticSourceTranslationPoolIcmpEcho,
		ltmFwNatStaticSourceTranslationPoolEgressIfcsEnabled
	}
	STATUS	 current
	DESCRIPTION
		"A collection of objects of ltmFwNatStaticSourceTranslationPool MIB."
	::= { bigipLocalTMGroups 203 }

ltmFwNatStaticSourceTranslationPoolStatGroup OBJECT-GROUP
	 OBJECTS {
		ltmFwNatStaticSourceTranslationPoolStatResetStats,
		ltmFwNatStaticSourceTranslationPoolStatNumber,
		ltmFwNatStaticSourceTranslationPoolStatName,
		ltmFwNatStaticSourceTranslationPoolStatTransReqs,
		ltmFwNatStaticSourceTranslationPoolStatTransReqFails,
		ltmFwNatStaticSourceTranslationPoolStatBidirReqs,
		ltmFwNatStaticSourceTranslationPoolStatBidirReqFails,
		ltmFwNatStaticSourceTranslationPoolStatErrAddrTrans,
		ltmFwNatStaticSourceTranslationPoolStatErrPortTrans,
		ltmFwNatStaticSourceTranslationPoolStatErrFlowCollis,
		ltmFwNatStaticSourceTranslationPoolStatErrCfgMismtch,
		ltmFwNatStaticSourceTranslationPoolStatErrMemory,
		ltmFwNatStaticSourceTranslationPoolStatSubscrIdLkps,
		ltmFwNatStaticSourceTranslationPoolStatSubscrIdNotFd,
		ltmFwNatStaticSourceTranslationPoolStatSubscrIdErrs
	}
	STATUS	 current
	DESCRIPTION
		"A collection of objects of ltmFwNatStaticSourceTranslationPoolStat MIB."
	::= { bigipLocalTMGroups 204 }
END
