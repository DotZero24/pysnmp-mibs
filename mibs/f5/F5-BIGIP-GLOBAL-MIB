F5-BIGIP-GLOBAL-MIB DEFINITIONS ::= BEGIN
--================================================================
-- F5-BIGIP-GLOBAL-MIB
--     A private enterprise MIB for F5 global traffic management
--     systems.
--     VERSION: 15.1.0.4
--================================================================

IMPORTS
    OBJECT-TYPE, NOTIFICATION-TYPE, MODULE-IDENTITY,
    Opaque, enterprises, Counter32, Counter64, TimeTicks
        FROM SNMPv2-SMI

    Gauge
        FROM RFC1155-SMI

    TEXTUAL-CONVENTION, MacAddress
        FROM SNMPv2-TC

    OBJECT-GROUP, MODULE-COMPLIANCE
        FROM SNMPv2-CONF

    InetAddress, InetAddressType, InetPortNumber
      FROM INET-ADDRESS-MIB

    bigipTrafficMgmt, bigipCompliances, bigipGroups, LongDisplayString
      FROM F5-BIGIP-COMMON-MIB;

--================================================================
bigipGlobalTM MODULE-IDENTITY
    LAST-UPDATED "201801292200Z" -- Mon Jan 29 22:00:01 UTC 2018
    ORGANIZATION "F5 Networks, Inc."
    CONTACT-INFO
         "postal: F5 Networks, Inc.
	 	  401 Elliott Ave. West
                  Seattle, WA 98119
          phone:  (206) 272-5555
          email:  support@f5.com"

    DESCRIPTION
        "Top-level infrastructure of the F5 enterprise MIB tree."
    ::= { bigipTrafficMgmt 3 }

--================================================================

-- bigipGlobalTM
gtmGlobals               OBJECT IDENTIFIER ::= { bigipGlobalTM 1 }
gtmApplications          OBJECT IDENTIFIER ::= { bigipGlobalTM 2 }
gtmDataCenters           OBJECT IDENTIFIER ::= { bigipGlobalTM 3 }
gtmIps                   OBJECT IDENTIFIER ::= { bigipGlobalTM 4 }
gtmLinks                 OBJECT IDENTIFIER ::= { bigipGlobalTM 5 }
gtmPools                 OBJECT IDENTIFIER ::= { bigipGlobalTM 6 }
gtmRegions               OBJECT IDENTIFIER ::= { bigipGlobalTM 7 }
gtmRules                 OBJECT IDENTIFIER ::= { bigipGlobalTM 8 }
gtmServers               OBJECT IDENTIFIER ::= { bigipGlobalTM 9 }
gtmTopologies            OBJECT IDENTIFIER ::= { bigipGlobalTM 10 }
gtmVirtualServers        OBJECT IDENTIFIER ::= { bigipGlobalTM 11}
gtmWideips               OBJECT IDENTIFIER ::= { bigipGlobalTM 12 }
gtmProberPools           OBJECT IDENTIFIER ::= { bigipGlobalTM 13 }
gtmDNSSEC                OBJECT IDENTIFIER ::= { bigipGlobalTM 14 }
gtmDevices               OBJECT IDENTIFIER ::= { bigipGlobalTM 15 }
gtmDeviceIps             OBJECT IDENTIFIER ::= { bigipGlobalTM 16 }
gtmLinkIps               OBJECT IDENTIFIER ::= { bigipGlobalTM 17 }

--gtmGlobals
gtmGlobalAttrs           OBJECT IDENTIFIER ::= { gtmGlobals 1 }
gtmGlobalStats           OBJECT IDENTIFIER ::= { gtmGlobals 2 }
gtmGlobalAttr            OBJECT IDENTIFIER ::= { gtmGlobalAttrs 1 }
gtmGlobalLdnsProbeProto  OBJECT IDENTIFIER ::= { gtmGlobalAttrs 2 }
gtmGlobalAttr2           OBJECT IDENTIFIER ::= { gtmGlobalAttrs 3 }
gtmGlobalStat            OBJECT IDENTIFIER ::= { gtmGlobalStats 1 }
gtmGlobalDnssecStat      OBJECT IDENTIFIER ::= { gtmGlobalStats 2 }

--gtmApplications
gtmApplication           OBJECT IDENTIFIER ::= { gtmApplications 1 }
gtmApplicationStatus     OBJECT IDENTIFIER ::= { gtmApplications 2 }
gtmAppContextStat        OBJECT IDENTIFIER ::= { gtmApplications 3 }
gtmAppContextDisable     OBJECT IDENTIFIER ::= { gtmApplications 4 }
gtmApplicationWideip     OBJECT IDENTIFIER ::= { gtmApplications 5 }

--gtmDataCenters
gtmDataCenter            OBJECT IDENTIFIER ::= { gtmDataCenters 1 }
gtmDataCenterStat        OBJECT IDENTIFIER ::= { gtmDataCenters 2 }
gtmDataCenterStatus      OBJECT IDENTIFIER ::= { gtmDataCenters 3 }

--gtmIps
gtmIp                    OBJECT IDENTIFIER ::= { gtmIps 1 }

--gtmLinks
gtmLink                  OBJECT IDENTIFIER ::= { gtmLinks 1 }
gtmLinkCost              OBJECT IDENTIFIER ::= { gtmLinks 2 }
gtmLinkStat              OBJECT IDENTIFIER ::= { gtmLinks 3 }
gtmLinkStatus            OBJECT IDENTIFIER ::= { gtmLinks 4 }

--gtmPools
gtmPool                  OBJECT IDENTIFIER ::= { gtmPools 1 }
gtmPoolStat              OBJECT IDENTIFIER ::= { gtmPools 2 }
gtmPoolStatus            OBJECT IDENTIFIER ::= { gtmPools 3 }
gtmPoolMember            OBJECT IDENTIFIER ::= { gtmPools 4 }
gtmPoolMemberDepends     OBJECT IDENTIFIER ::= { gtmPools 5 }
gtmPoolMemberStat        OBJECT IDENTIFIER ::= { gtmPools 6 }
gtmPoolMemberStatus      OBJECT IDENTIFIER ::= { gtmPools 7 }

--gtmRegions
gtmRegionEntry           OBJECT IDENTIFIER ::= { gtmRegions 1 }
gtmRegItem               OBJECT IDENTIFIER ::= { gtmRegions 2 }

--gtmRules
gtmRule                  OBJECT IDENTIFIER ::= { gtmRules 1 }
gtmRuleEvent             OBJECT IDENTIFIER ::= { gtmRules 2 }
gtmRuleEventStat         OBJECT IDENTIFIER ::= { gtmRules 3 }

--gtmServers
gtmServer                OBJECT IDENTIFIER ::= { gtmServers 1 }
gtmServerStat            OBJECT IDENTIFIER ::= { gtmServers 2 }
gtmServerStatus          OBJECT IDENTIFIER ::= { gtmServers 3 }
gtmServerStat2           OBJECT IDENTIFIER ::= { gtmServers 4 }

--gtmTopItems
gtmTopItem               OBJECT IDENTIFIER ::= { gtmTopologies 1 }

--gtmVirtualServers
gtmVirtualServ           OBJECT IDENTIFIER ::= { gtmVirtualServers 1 }
gtmVirtualServDepends    OBJECT IDENTIFIER ::= { gtmVirtualServers 2 }
gtmVirtualServStat       OBJECT IDENTIFIER ::= { gtmVirtualServers 3 }
gtmVirtualServStatus     OBJECT IDENTIFIER ::= { gtmVirtualServers 4 }

--gtmWideips
gtmWideip                OBJECT IDENTIFIER ::= { gtmWideips 1 }
gtmWideipStat            OBJECT IDENTIFIER ::= { gtmWideips 2 }
gtmWideipStatus          OBJECT IDENTIFIER ::= { gtmWideips 3 }
gtmWideipAlias           OBJECT IDENTIFIER ::= { gtmWideips 4 }
gtmWideipPool            OBJECT IDENTIFIER ::= { gtmWideips 5 }
gtmWideipRule            OBJECT IDENTIFIER ::= { gtmWideips 6 }

--gtmProberPools
gtmProberPool                  OBJECT IDENTIFIER ::= { gtmProberPools 1 }
gtmProberPoolStat              OBJECT IDENTIFIER ::= { gtmProberPools 2 }
gtmProberPoolStatus            OBJECT IDENTIFIER ::= { gtmProberPools 3 }
gtmProberPoolMember            OBJECT IDENTIFIER ::= { gtmProberPools 4 }
gtmProberPoolMemberStat        OBJECT IDENTIFIER ::= { gtmProberPools 5 }
gtmProberPoolMemberStatus      OBJECT IDENTIFIER ::= { gtmProberPools 6 }

--gtmDNSSEC
gtmDnssecZoneStat        OBJECT IDENTIFIER ::= { gtmDNSSEC 1 }

--gtmDevices
gtmDevice                OBJECT IDENTIFIER ::= { gtmDevices 1 }
gtmDeviceStat            OBJECT IDENTIFIER ::= { gtmDevices 2 }
gtmDeviceStatus          OBJECT IDENTIFIER ::= { gtmDevices 3 }

--gtmDeviceIps
gtmDeviceIp              OBJECT IDENTIFIER ::= { gtmDeviceIps 1 }

--gtmLinkIps
gtmLinkIp                OBJECT IDENTIFIER ::= { gtmLinkIps 1 }



--==================================================================
-- Gtm_globals
--==================================================================
gtmAttrDumpTopology OBJECT-TYPE
	SYNTAX INTEGER {
		false(0),
		true(1)
	}
	MAX-ACCESS read-only
	STATUS	 deprecated
	DESCRIPTION
		"Deprecated!.
		The state indicating whether or not to dump the topology."
	::= { gtmGlobalAttr 1 }

gtmAttrCacheLdns OBJECT-TYPE
	SYNTAX INTEGER {
		false(0),
		true(1)
	}
	MAX-ACCESS read-only
	STATUS	 deprecated
	DESCRIPTION
		"Deprecated!.
		The state indicating whether or not to cache LDNSes."
	::= { gtmGlobalAttr 2 }

gtmAttrAolAware OBJECT-TYPE
	SYNTAX INTEGER {
		false(0),
		true(1)
	}
	MAX-ACCESS read-only
	STATUS	 deprecated
	DESCRIPTION
		"Deprecated!.
		The state indicating whether or not local DNS servers that
		belong to AOL (America Online) are recognized."
	::= { gtmGlobalAttr 3 }

gtmAttrCheckStaticDepends OBJECT-TYPE
	SYNTAX INTEGER {
		false(0),
		true(1)
	}
	MAX-ACCESS read-only
	STATUS	 deprecated
	DESCRIPTION
		"Deprecated!.
		The state indicating whether or not to check the availability
		of virtual servers."
	::= { gtmGlobalAttr 4 }

gtmAttrCheckDynamicDepends OBJECT-TYPE
	SYNTAX INTEGER {
		false(0),
		true(1)
	}
	MAX-ACCESS read-only
	STATUS	 deprecated
	DESCRIPTION
		"Deprecated!.
		The state indicating whether or not to check availability of
		a path before it uses the path for load balancing."
	::= { gtmGlobalAttr 5 }

gtmAttrDrainRequests OBJECT-TYPE
	SYNTAX INTEGER {
		false(0),
		true(1)
	}
	MAX-ACCESS read-only
	STATUS	 deprecated
	DESCRIPTION
		"Deprecated!.
		The state indicating whether or not persistent connections
		are allowed to remain connected, until TTL expires,
		when disabling a pool."
	::= { gtmGlobalAttr 6 }

gtmAttrEnableResetsRipeness OBJECT-TYPE
	SYNTAX INTEGER {
		false(0),
		true(1)
	}
	MAX-ACCESS read-only
	STATUS	 deprecated
	DESCRIPTION
		"Deprecated!.
		The state indicating whether or not ripeness value is allowed
		to be reset."
	::= { gtmGlobalAttr 7 }

gtmAttrFbRespectDepends OBJECT-TYPE
	SYNTAX INTEGER {
		false(0),
		true(1)
	}
	MAX-ACCESS read-only
	STATUS	 deprecated
	DESCRIPTION
		"Deprecated!.
		The state indicating whether or not to respect virtual server
		status when load balancing switches to the fallback mode."
	::= { gtmGlobalAttr 8 }

gtmAttrFbRespectAcl OBJECT-TYPE
	SYNTAX INTEGER {
		false(0),
		true(1)
	}
	MAX-ACCESS read-only
	STATUS	 deprecated
	DESCRIPTION
		"Deprecated!.
		Deprecated! The state indicating whether or not to respect ACL.
	         This is part of an outdated mechanism for disabling virtual servers"
	::= { gtmGlobalAttr 9 }

gtmAttrDefaultAlternate OBJECT-TYPE
	SYNTAX INTEGER {
		returntodns(0),
		null(1),
		roundrobin(2),
		ratio(3),
		topology(4),
		statpersist(5),
		ga(6),
		vscapacity(7),
		leastconn(8),
		lowestrtt(9),
		lowesthops(10),
		packetrate(11),
		cpu(12),
		hitratio(13),
		qos(14),
		bps(15),
		droppacket(16),
		explicitip(17),
		vssore(18)
	}
	MAX-ACCESS read-only
	STATUS	 deprecated
	DESCRIPTION
		"Deprecated!.
		The default alternate LB method."
	::= { gtmGlobalAttr 10 }

gtmAttrDefaultFallback OBJECT-TYPE
	SYNTAX INTEGER {
		returntodns(0),
		null(1),
		roundrobin(2),
		ratio(3),
		topology(4),
		statpersit(5),
		ga(6),
		vscapacity(7),
		leastconn(8),
		lowestrtt(9),
		lowesthops(10),
		packetrate(11),
		cpu(12),
		hitratio(13),
		qos(14),
		bps(15),
		droppacket(16),
		explicitip(17),
		vsscore(18)
	}
	MAX-ACCESS read-only
	STATUS	 deprecated
	DESCRIPTION
		"Deprecated!.
		The default fallback LB method."
	::= { gtmGlobalAttr 11 }

gtmAttrPersistMask OBJECT-TYPE
	SYNTAX Gauge
	MAX-ACCESS read-only
	STATUS	 deprecated
	DESCRIPTION
		"Deprecated!.
		Deprecated! Replaced by gtmAttrStaticPersistCidr and gtmAttrStaticPersistV6Cidr.
		The persistence mask which is used to determine the netmask applied
		for static persistance requests."
	::= { gtmGlobalAttr 12 }

gtmAttrGtmSetsRecursion OBJECT-TYPE
	SYNTAX INTEGER {
		false(0),
		true(1)
	}
	MAX-ACCESS read-only
	STATUS	 deprecated
	DESCRIPTION
		"Deprecated!.
		The state indicating whether set recursion by global
		traffic management object(GTM) is enable or not."
	::= { gtmGlobalAttr 13 }

gtmAttrQosFactorLcs OBJECT-TYPE
	SYNTAX Gauge
	MAX-ACCESS read-only
	STATUS	 deprecated
	DESCRIPTION
		"Deprecated!.
		The factor used to normalize link capacity values
		when the load balancing mode is set to LB_METHOD_QOS."
	::= { gtmGlobalAttr 14 }

gtmAttrQosFactorRtt OBJECT-TYPE
	SYNTAX Gauge
	MAX-ACCESS read-only
	STATUS	 deprecated
	DESCRIPTION
		"Deprecated!.
		The factor used to normalize round-trip time values
		when the load balancing mode is set to LB_METHOD_QOS."
	::= { gtmGlobalAttr 15 }

gtmAttrQosFactorHops OBJECT-TYPE
	SYNTAX Gauge
	MAX-ACCESS read-only
	STATUS	 deprecated
	DESCRIPTION
		"Deprecated!.
		The factor used to normalize hops when the load
		balancing mode is set to LB_METHOD_QOS."
	::= { gtmGlobalAttr 16 }

gtmAttrQosFactorHitRatio OBJECT-TYPE
	SYNTAX Gauge
	MAX-ACCESS read-only
	STATUS	 deprecated
	DESCRIPTION
		"Deprecated!.
		The factor used to normalize ping packet completion
		rates when the load balancing mode is set to LB_METHOD_QOS."
	::= { gtmGlobalAttr 17 }

gtmAttrQosFactorPacketRate OBJECT-TYPE
	SYNTAX Gauge
	MAX-ACCESS read-only
	STATUS	 deprecated
	DESCRIPTION
		"Deprecated!.
		The factor used to normalize packet rates when the load
		balancing mode is set to LB_METHOD_QOS."
	::= { gtmGlobalAttr 18 }

gtmAttrQosFactorBps OBJECT-TYPE
	SYNTAX Gauge
	MAX-ACCESS read-only
	STATUS	 deprecated
	DESCRIPTION
		"Deprecated!.
		The factor used to normalize kilobytes per second
		when the load balancing mode is set to LB_METHOD_QOS."
	::= { gtmGlobalAttr 19 }

gtmAttrQosFactorVsCapacity OBJECT-TYPE
	SYNTAX Gauge
	MAX-ACCESS read-only
	STATUS	 deprecated
	DESCRIPTION
		"Deprecated!.
		The factor used to normalize virtual server capacity
		values when the load balancing mode is set to LB_METHOD_QOS."
	::= { gtmGlobalAttr 20 }

gtmAttrQosFactorTopology OBJECT-TYPE
	SYNTAX Gauge
	MAX-ACCESS read-only
	STATUS	 deprecated
	DESCRIPTION
		"Deprecated!.
		The factor used to normalize topology values when the load
		balancing mode is set to LB_METHOD_QOS."
	::= { gtmGlobalAttr 21 }

gtmAttrQosFactorConnRate OBJECT-TYPE
	SYNTAX Gauge
	MAX-ACCESS read-only
	STATUS	 deprecated
	DESCRIPTION
		"Deprecated!.
		Deprecated!
		Replaced by gtmAttrQosFactorVsScore.
		The factor used to normalize connection rates when the load
		balancing mode is set to LB_METHOD_QOS."
	::= { gtmGlobalAttr 22 }

gtmAttrTimerRetryPathData OBJECT-TYPE
	SYNTAX Gauge
	MAX-ACCESS read-only
	STATUS	 deprecated
	DESCRIPTION
		"Deprecated!.
		The frequency at which to retrieve path data."
	::= { gtmGlobalAttr 23 }

gtmAttrTimerGetAutoconfigData OBJECT-TYPE
	SYNTAX Gauge
	MAX-ACCESS read-only
	STATUS	 deprecated
	DESCRIPTION
		"Deprecated!.
		The frequency at which to retrieve auto-configuration data."
	::= { gtmGlobalAttr 24 }

gtmAttrTimerPersistCache OBJECT-TYPE
	SYNTAX Gauge
	MAX-ACCESS read-only
	STATUS	 deprecated
	DESCRIPTION
		"Deprecated!.
		The frequency at which to retrieve path and metrics
		data from the system cache."
	::= { gtmGlobalAttr 25 }

gtmAttrDefaultProbeLimit OBJECT-TYPE
	SYNTAX Gauge
	MAX-ACCESS read-only
	STATUS	 deprecated
	DESCRIPTION
		"Deprecated!.
		The default probe limit, the number of times to probe a path."
	::= { gtmGlobalAttr 26 }

gtmAttrDownThreshold OBJECT-TYPE
	SYNTAX Gauge
	MAX-ACCESS read-only
	STATUS	 deprecated
	DESCRIPTION
		"Deprecated!.
		The down_threshold value. If a host server or a host virtual server
		has been marked down for the last down_threshold probing cycles
		(timer_get_host_data or timer_get_vs_data respectively), then perform
		service checks every down_multiple * timer period instead."
	::= { gtmGlobalAttr 27 }

gtmAttrDownMultiple OBJECT-TYPE
	SYNTAX Gauge
	MAX-ACCESS read-only
	STATUS	 deprecated
	DESCRIPTION
		"Deprecated!.
		The down_multiple value. If a host server or a host virtual server
		has been marked down for the last down_threshold probing cycles
		(timer_get_host_data or timer_get_vs_data respectively), then perform
		service checks every down_multiple * timer period instead."
	::= { gtmGlobalAttr 28 }

gtmAttrPathTtl OBJECT-TYPE
	SYNTAX Gauge
	MAX-ACCESS read-only
	STATUS	 deprecated
	DESCRIPTION
		"Deprecated!.
		The TTL for the path information."
	::= { gtmGlobalAttr 29 }

gtmAttrTraceTtl OBJECT-TYPE
	SYNTAX Gauge
	MAX-ACCESS read-only
	STATUS	 deprecated
	DESCRIPTION
		"Deprecated!.
		The TTL for the traceroute information."
	::= { gtmGlobalAttr 30 }

gtmAttrLdnsDuration OBJECT-TYPE
	SYNTAX Gauge
	MAX-ACCESS read-only
	STATUS	 deprecated
	DESCRIPTION
		"Deprecated!.
		The number of seconds that an inactive LDNS remains cached."
	::= { gtmGlobalAttr 31 }

gtmAttrPathDuration OBJECT-TYPE
	SYNTAX Gauge
	MAX-ACCESS read-only
	STATUS	 deprecated
	DESCRIPTION
		"Deprecated!.
		The number of seconds that a path remains cached after its last access."
	::= { gtmGlobalAttr 32 }

gtmAttrRttSampleCount OBJECT-TYPE
	SYNTAX Gauge
	MAX-ACCESS read-only
	STATUS	 deprecated
	DESCRIPTION
		"Deprecated!.
		The number of packets to send out in a probe request to determine
		path information."
	::= { gtmGlobalAttr 33 }

gtmAttrRttPacketLength OBJECT-TYPE
	SYNTAX Gauge
	MAX-ACCESS read-only
	STATUS	 deprecated
	DESCRIPTION
		"Deprecated!.
		The length of the packet sent out in a probe request to determine
		path information."
	::= { gtmGlobalAttr 34 }

gtmAttrRttTimeout OBJECT-TYPE
	SYNTAX Gauge
	MAX-ACCESS read-only
	STATUS	 deprecated
	DESCRIPTION
		"Deprecated!.
		The timeout for RTT, in seconds."
	::= { gtmGlobalAttr 35 }

gtmAttrMaxMonReqs OBJECT-TYPE
	SYNTAX Gauge
	MAX-ACCESS read-only
	STATUS	 deprecated
	DESCRIPTION
		"Deprecated!.
		The maximum synchronous monitor request, which is used to control
		the maximum number of monitor requests being sent out at one time
		for a given probing interval. This will allow the user to smooth out
		monitor probe requests as much as they desire."
	::= { gtmGlobalAttr 36 }

gtmAttrTraceroutePort OBJECT-TYPE
	SYNTAX Gauge
	MAX-ACCESS read-only
	STATUS	 deprecated
	DESCRIPTION
		"Deprecated!.
		The port to use to collect traceroute (hops) data."
	::= { gtmGlobalAttr 37 }

gtmAttrPathsNeverDie OBJECT-TYPE
	SYNTAX INTEGER {
		false(0),
		true(1)
	}
	MAX-ACCESS read-only
	STATUS	 deprecated
	DESCRIPTION
		"Deprecated!.
		The state indicating whether the dynamic load balancing modes
		can use path data even after the TTL for the path data has expired."
	::= { gtmGlobalAttr 38 }

gtmAttrProbeDisabledObjects OBJECT-TYPE
	SYNTAX INTEGER {
		false(0),
		true(1)
	}
	MAX-ACCESS read-only
	STATUS	 deprecated
	DESCRIPTION
		"Deprecated!.
		The state indicating whether probing disabled objects by global
		traffic management object(GTM) is enabled or not."
	::= { gtmGlobalAttr 39 }

gtmAttrLinkLimitFactor OBJECT-TYPE
	SYNTAX Gauge
	MAX-ACCESS read-only
	STATUS	 deprecated
	DESCRIPTION
		"Deprecated!.
		The link limit factor, which is used to set a target percentage
		for traffic. For example, if it is set to 90, the ratio cost
		based load-balancing will set a ratio with a maximum value equal
		to 90% of the limit value for the link. Default is 95%."
	::= { gtmGlobalAttr 40 }

gtmAttrOverLimitLinkLimitFactor OBJECT-TYPE
	SYNTAX Gauge
	MAX-ACCESS read-only
	STATUS	 deprecated
	DESCRIPTION
		"Deprecated!.
		The over-limit link limit factor. If traffic on a link exceeds
		the limit, this factor will be used instead of the link_limit_factor
		until the traffic is over limit for more than max_link_over_limit_count
		times. Once the limit has been exceeded too many times, all traffic
		is shut off for the link. The default for
		over_limit_link_limit_factor is 90%."
	::= { gtmGlobalAttr 41 }

gtmAttrLinkPrepaidFactor OBJECT-TYPE
	SYNTAX Gauge
	MAX-ACCESS read-only
	STATUS	 deprecated
	DESCRIPTION
		"Deprecated!.
		The link prepaid factor. Maximum percentage of traffic allocated
		to link which has a traffic allotment which has been prepaid.
		Default is 95%."
	::= { gtmGlobalAttr 42 }

gtmAttrLinkCompensateInbound OBJECT-TYPE
	SYNTAX Gauge
	MAX-ACCESS read-only
	STATUS	 deprecated
	DESCRIPTION
		"Deprecated!.
		The link compensate inbound. If set, the link allotment calculation
		will take into account traffic which does not flow through the BIGIP,
		i.e. if more traffic is flowing through a link as measured by SNMP
		on the router than is flowing through the BIGIP. This applies to
		inbound traffic which the major volume will initiate from internal
		clients."
	::= { gtmGlobalAttr 43 }

gtmAttrLinkCompensateOutbound OBJECT-TYPE
	SYNTAX Gauge
	MAX-ACCESS read-only
	STATUS	 deprecated
	DESCRIPTION
		"Deprecated!.
		The link compensate outbound. If set, the link allotment calculation
		will take into account traffic which does not flow through the BIGIP,
		i.e. if more traffic is flowing through a link as measured by SNMP
		on the router than is flowing through the BIGIP. This applies to
		outbound traffic which the major volume will initiate from internal
		clients."
	::= { gtmGlobalAttr 44 }

gtmAttrLinkCompensationHistory OBJECT-TYPE
	SYNTAX Gauge
	MAX-ACCESS read-only
	STATUS	 deprecated
	DESCRIPTION
		"Deprecated!.
		The link compensation history."
	::= { gtmGlobalAttr 45 }

gtmAttrMaxLinkOverLimitCount OBJECT-TYPE
	SYNTAX Gauge
	MAX-ACCESS read-only
	STATUS	 deprecated
	DESCRIPTION
		"Deprecated!.
		The maximum link over limit count. The count of how many times
		in a row traffic may be over the defined limit for the link before
		it is shut off entirely. Default is 1."
	::= { gtmGlobalAttr 46 }

gtmAttrLowerBoundPctRow OBJECT-TYPE
	SYNTAX Gauge
	MAX-ACCESS read-only
	STATUS	 deprecated
	DESCRIPTION
		"Deprecated!.
		Deprecated! No longer useful.
	        The lower bound percentage row option in Internet Weather Map."
	::= { gtmGlobalAttr 47 }

gtmAttrLowerBoundPctCol OBJECT-TYPE
	SYNTAX Gauge
	MAX-ACCESS read-only
	STATUS	 deprecated
	DESCRIPTION
		"Deprecated!.
		Deprecated! No longer useful.
	        The lower bound percentage column option in Internet Weather Map."
	::= { gtmGlobalAttr 48 }

gtmAttrAutoconf OBJECT-TYPE
	SYNTAX INTEGER {
		false(0),
		true(1)
	}
	MAX-ACCESS read-only
	STATUS	 deprecated
	DESCRIPTION
		"Deprecated!.
		The state indicating whether to auto configure BIGIP/3DNS servers
		(automatic addition and deletion of self IPs and virtual servers)."
	::= { gtmGlobalAttr 49 }

gtmAttrAutosync OBJECT-TYPE
	SYNTAX INTEGER {
		false(0),
		true(1)
	}
	MAX-ACCESS read-only
	STATUS	 deprecated
	DESCRIPTION
		"Deprecated!.
		The state indicating whether or not to autosync.
		Allows automatic updates of wideip.conf to/from other 3-DNSes."
	::= { gtmGlobalAttr 50 }

gtmAttrSyncNamedConf OBJECT-TYPE
	SYNTAX INTEGER {
		false(0),
		true(1)
	}
	MAX-ACCESS read-only
	STATUS	 deprecated
	DESCRIPTION
		"Deprecated!.
		The state indicating whether or not to auto-synchronize named
		configuration. Allows automatic updates of named.conf to/from other 3-DNSes."
	::= { gtmGlobalAttr 51 }

gtmAttrSyncGroup OBJECT-TYPE
	SYNTAX LongDisplayString
	MAX-ACCESS read-only
	STATUS	 deprecated
	DESCRIPTION
		"Deprecated!.
		The name of sync group."
	::= { gtmGlobalAttr 52 }

gtmAttrSyncTimeout OBJECT-TYPE
	SYNTAX Gauge
	MAX-ACCESS read-only
	STATUS	 deprecated
	DESCRIPTION
		"Deprecated!.
		The sync timeout.  If synch'ing from a remote 3-DNS takes longer than
		this timeout, then abort the connection."
	::= { gtmGlobalAttr 53 }

gtmAttrSyncZonesTimeout OBJECT-TYPE
	SYNTAX Gauge
	MAX-ACCESS read-only
	STATUS	 deprecated
	DESCRIPTION
		"Deprecated!.
		The sync zones timeout. If synch'ing named and zone configuration
		takes this timeout, then abort the connection."
	::= { gtmGlobalAttr 54 }

gtmAttrTimeTolerance OBJECT-TYPE
	SYNTAX Gauge
	MAX-ACCESS read-only
	STATUS	 deprecated
	DESCRIPTION
		"Deprecated!.
		The allowable time difference for data to be out of sync between
		members of a sync group."
	::= { gtmGlobalAttr 55 }

gtmAttrTopologyLongestMatch OBJECT-TYPE
	SYNTAX INTEGER {
		false(0),
		true(1)
	}
	MAX-ACCESS read-only
	STATUS	 deprecated
	DESCRIPTION
		"Deprecated!.
		The state indicating  whether or not the 3-DNS Controller selects
		the topology record that is most specific and, thus, has the longest
		match, in cases where there are several IP/netmask items that match
		a particular IP address.
		If it is set to false, the 3-DNS Controller uses the first topology record
		that matches (according to the order of entry) in the topology statement."
	::= { gtmGlobalAttr 56 }

gtmAttrTopologyAclThreshold OBJECT-TYPE
	SYNTAX Gauge
	MAX-ACCESS read-only
	STATUS	 deprecated
	DESCRIPTION
		"Deprecated!.
		Deprecated! The threshold of the topology ACL.
	         This is an outdated mechanism for disabling a node."
	::= { gtmGlobalAttr 57 }

gtmAttrStaticPersistCidr OBJECT-TYPE
	SYNTAX Gauge
	MAX-ACCESS read-only
	STATUS	 deprecated
	DESCRIPTION
		"Deprecated!.
		The variable used with the static persistence load balancing mode
		to allow users to specify what cidr should be used.
		This is used for IPv4."
	::= { gtmGlobalAttr 58 }

gtmAttrStaticPersistV6Cidr OBJECT-TYPE
	SYNTAX Gauge
	MAX-ACCESS read-only
	STATUS	 deprecated
	DESCRIPTION
		"Deprecated!.
		The variable used with the static persistence load balancing mode
		to allow users to specify what cidr should be used.
		This is used for IPv6."
	::= { gtmGlobalAttr 59 }

gtmAttrQosFactorVsScore OBJECT-TYPE
	SYNTAX Gauge
	MAX-ACCESS read-only
	STATUS	 deprecated
	DESCRIPTION
		"Deprecated!.
		The factor used to normalize virtual server (VS) score
		when the load balancing mode is set to LB_METHOD_QOS."
	::= { gtmGlobalAttr 60 }

gtmAttrTimerSendKeepAlive OBJECT-TYPE
	SYNTAX Gauge
	MAX-ACCESS read-only
	STATUS	 deprecated
	DESCRIPTION
		"Deprecated!.
		The frequency of GTM keep alive messages (strictly the config timestamps)."
	::= { gtmGlobalAttr 61 }

gtmAttrCertificateDepth OBJECT-TYPE
	SYNTAX Gauge
	MAX-ACCESS read-only
	STATUS	 deprecated
	DESCRIPTION
		"Deprecated!.
		Deprecated! No longer updated.
	        When non-zero, customers may use their own SSL certificates by setting the certificate depth."
	::= { gtmGlobalAttr 62 }

gtmAttrMaxMemoryUsage OBJECT-TYPE
	SYNTAX Gauge
	MAX-ACCESS read-only
	STATUS	 deprecated
	DESCRIPTION
		"Deprecated!.
		Deprecated! The maximum amount of memory (in MB) allocated to GTM."
	::= { gtmGlobalAttr 63 }

--==================================================================
-- Gtm_globals_ldns_probe_protocols
--==================================================================
gtmGlobalLdnsProbeProtoNumber OBJECT-TYPE
	SYNTAX INTEGER
	MAX-ACCESS read-only
	STATUS current
	DESCRIPTION
		"The number of gtmGlobalLdnsProbeProto entries in the table."
	::= { gtmGlobalLdnsProbeProto 1 }

gtmGlobalLdnsProbeProtoTable OBJECT-TYPE
	SYNTAX SEQUENCE OF GtmGlobalLdnsProbeProtoEntry
	MAX-ACCESS not-accessible
	STATUS current
	DESCRIPTION
		"A table containing information of global LDNS probe protocols for GTM (Global Traffic Management)."
	::= { gtmGlobalLdnsProbeProto 2 }

gtmGlobalLdnsProbeProtoEntry OBJECT-TYPE
	SYNTAX  GtmGlobalLdnsProbeProtoEntry
	MAX-ACCESS not-accessible
	STATUS current
	DESCRIPTION
		"Columns in the gtmGlobalLdnsProbeProto Table"
	INDEX {
		gtmGlobalLdnsProbeProtoName,
		gtmGlobalLdnsProbeProtoIndex
	}
	::= { gtmGlobalLdnsProbeProtoTable 1 }

GtmGlobalLdnsProbeProtoEntry ::=
	SEQUENCE {
        	gtmGlobalLdnsProbeProtoIndex                              INTEGER,
        	gtmGlobalLdnsProbeProtoType                               INTEGER,
        	gtmGlobalLdnsProbeProtoName                               LongDisplayString
	}

gtmGlobalLdnsProbeProtoIndex OBJECT-TYPE
	SYNTAX INTEGER(0..2147483647)
	MAX-ACCESS read-only
	STATUS current
	DESCRIPTION
		"The index of LDNS probe protocols."
	::= { gtmGlobalLdnsProbeProtoEntry 1 }

gtmGlobalLdnsProbeProtoType OBJECT-TYPE
	SYNTAX INTEGER {
		icmp(0),
		tcp(1),
		udp(2),
		dnsdot(3),
		dnsrev(4)
	}
	MAX-ACCESS read-only
	STATUS current
	DESCRIPTION
		"The LDNS probe protocol. The less index is, the more preferred protocol is."
	::= { gtmGlobalLdnsProbeProtoEntry 2 }

gtmGlobalLdnsProbeProtoName OBJECT-TYPE
	SYNTAX LongDisplayString
	MAX-ACCESS read-only
	STATUS current
	DESCRIPTION
		"name as a key."
	::= { gtmGlobalLdnsProbeProtoEntry 3 }

--==================================================================
-- Gtm_global_stat
--==================================================================
gtmStatResetStats OBJECT-TYPE
	SYNTAX INTEGER
	MAX-ACCESS read-write
	STATUS current
	DESCRIPTION
		"The action to reset resettable statistics data in gtmGlobalStat.
		 Setting this value to 1 will reset statistics data.
		 Note, some statistics data may not be reset including data that are incremental counters."
	::= { gtmGlobalStat 1 }

gtmStatRequests OBJECT-TYPE
	SYNTAX Counter64
	MAX-ACCESS read-only
	STATUS current
	DESCRIPTION
		"The number of total requests for wide IPs for GTM (Global Traffic Management)."
	::= { gtmGlobalStat 2 }

gtmStatResolutions OBJECT-TYPE
	SYNTAX Counter64
	MAX-ACCESS read-only
	STATUS current
	DESCRIPTION
		"The number of total resolutions for wide IPs for GTM (Global Traffic Management)."
	::= { gtmGlobalStat 3 }

gtmStatPersisted OBJECT-TYPE
	SYNTAX Counter64
	MAX-ACCESS read-only
	STATUS current
	DESCRIPTION
		"The number of persisted requests for wide IPs for GTM (Global Traffic Management)."
	::= { gtmGlobalStat 4 }

gtmStatPreferred OBJECT-TYPE
	SYNTAX Counter64
	MAX-ACCESS read-only
	STATUS current
	DESCRIPTION
		"The number of times which the preferred load balance method is used
		for wide IPs for GTM (Global Traffic Management)."
	::= { gtmGlobalStat 5 }

gtmStatAlternate OBJECT-TYPE
	SYNTAX Counter64
	MAX-ACCESS read-only
	STATUS current
	DESCRIPTION
		"The number of times which the alternate load balance method is used
	        for wide IPs for GTM (Global Traffic Management)."
	::= { gtmGlobalStat 6 }

gtmStatFallback OBJECT-TYPE
	SYNTAX Counter64
	MAX-ACCESS read-only
	STATUS current
	DESCRIPTION
		"The number of times which the alternate load balance method is used
	        for wide IPs for GTM (Global Traffic Management)."
	::= { gtmGlobalStat 7 }

gtmStatDropped OBJECT-TYPE
	SYNTAX Counter64
	MAX-ACCESS read-only
	STATUS current
	DESCRIPTION
		"The number of dropped DNS messages for wide IPs for GTM (Global Traffic Management)."
	::= { gtmGlobalStat 8 }

gtmStatExplicitIp OBJECT-TYPE
	SYNTAX Counter64
	MAX-ACCESS read-only
	STATUS	 deprecated
	DESCRIPTION
		"Deprecated! The number of times which a LDNS  was persisted to wide IPs
	        by the explicit IP rule for GTM (Global Traffic Management)."
	::= { gtmGlobalStat 9 }

gtmStatReturnToDns OBJECT-TYPE
	SYNTAX Counter64
	MAX-ACCESS read-only
	STATUS current
	DESCRIPTION
		"The number of times which a resolve was returned to DNS (for resolution)
	        for wide IPs for GTM (Global Traffic Management)."
	::= { gtmGlobalStat 10 }

gtmStatReconnects OBJECT-TYPE
	SYNTAX Counter64
	MAX-ACCESS read-only
	STATUS current
	DESCRIPTION
		"The number of total reconnects for GTM (Global Traffic Management)."
	::= { gtmGlobalStat 11 }

gtmStatBytesReceived OBJECT-TYPE
	SYNTAX Counter64
	MAX-ACCESS read-only
	STATUS current
	DESCRIPTION
		"The total number of bytes received by the system for GTM (Global Traffic Management)."
	::= { gtmGlobalStat 12 }

gtmStatBytesSent OBJECT-TYPE
	SYNTAX Counter64
	MAX-ACCESS read-only
	STATUS current
	DESCRIPTION
		"The total number of bytes sent out by the system for GTM (Global Traffic Management)."
	::= { gtmGlobalStat 13 }

gtmStatNumBacklogged OBJECT-TYPE
	SYNTAX Counter64
	MAX-ACCESS read-only
	STATUS current
	DESCRIPTION
		"The number of times when a send action was backlogged for GTM (Global Traffic Management)."
	::= { gtmGlobalStat 14 }

gtmStatBytesDropped OBJECT-TYPE
	SYNTAX Counter64
	MAX-ACCESS read-only
	STATUS current
	DESCRIPTION
		"The total number of bytes dropped due to backlogged/unconnected
		for GTM (Global Traffic Management)."
	::= { gtmGlobalStat 15 }

gtmStatLdnses OBJECT-TYPE
	SYNTAX Gauge
	MAX-ACCESS read-only
	STATUS current
	DESCRIPTION
		"The total current LDNSes for GTM (Global Traffic Management)."
	::= { gtmGlobalStat 16 }

gtmStatPaths OBJECT-TYPE
	SYNTAX Gauge
	MAX-ACCESS read-only
	STATUS current
	DESCRIPTION
		"The total current paths for GTM (Global Traffic Management)."
	::= { gtmGlobalStat 17 }

gtmStatReturnFromDns OBJECT-TYPE
	SYNTAX Counter64
	MAX-ACCESS read-only
	STATUS current
	DESCRIPTION
		"The number of times which a resolve was returned from DNS
	        for wide IPs for GTM (Global Traffic Management)."
	::= { gtmGlobalStat 18 }

gtmStatCnameResolutions OBJECT-TYPE
	SYNTAX Counter64
	MAX-ACCESS read-only
	STATUS current
	DESCRIPTION
		"The number of times which a query is resolved by the CNAME of pools
	        associated with a Wide IP for GTM (Global Traffic Management)."
	::= { gtmGlobalStat 19 }

gtmStatARequests OBJECT-TYPE
	SYNTAX Counter64
	MAX-ACCESS read-only
	STATUS current
	DESCRIPTION
		"The number of A requests for wide IPs for GTM (Global Traffic Management)."
	::= { gtmGlobalStat 20 }

gtmStatAaaaRequests OBJECT-TYPE
	SYNTAX Counter64
	MAX-ACCESS read-only
	STATUS current
	DESCRIPTION
		"The number of AAAA requests for wide IPs for GTM (Global Traffic Management)."
	::= { gtmGlobalStat 21 }

--==================================================================
-- Gtm_application
--==================================================================
gtmAppNumber OBJECT-TYPE
	SYNTAX INTEGER
	MAX-ACCESS read-only
	STATUS current
	DESCRIPTION
		"The number of gtmApplication entries in the table."
	::= { gtmApplication 1 }

gtmAppTable OBJECT-TYPE
	SYNTAX SEQUENCE OF GtmAppEntry
	MAX-ACCESS not-accessible
	STATUS current
	DESCRIPTION
		"A table containing information of applications for GTM (Global Traffic Management)."
	::= { gtmApplication 2 }

gtmAppEntry OBJECT-TYPE
	SYNTAX  GtmAppEntry
	MAX-ACCESS not-accessible
	STATUS current
	DESCRIPTION
		"Columns in the gtmApp Table"
	INDEX {
		gtmAppName
	}
	::= { gtmAppTable 1 }

GtmAppEntry ::=
	SEQUENCE {
        	gtmAppName                                                LongDisplayString,
        	gtmAppPersist                                             INTEGER,
        	gtmAppTtlPersist                                          Gauge,
        	gtmAppAvailability                                        INTEGER
	}

gtmAppName OBJECT-TYPE
	SYNTAX LongDisplayString
	MAX-ACCESS read-only
	STATUS current
	DESCRIPTION
		"The name of an application."
	::= { gtmAppEntry 1 }

gtmAppPersist OBJECT-TYPE
	SYNTAX INTEGER {
		false(0),
		true(1)
	}
	MAX-ACCESS read-only
	STATUS current
	DESCRIPTION
		"The state indicating whether persistence is enabled or not."
	::= { gtmAppEntry 2 }

gtmAppTtlPersist OBJECT-TYPE
	SYNTAX Gauge
	MAX-ACCESS read-only
	STATUS current
	DESCRIPTION
		"The persistence TTL value for the specified application."
	::= { gtmAppEntry 3 }

gtmAppAvailability OBJECT-TYPE
	SYNTAX INTEGER {
		none(0),
		server(1),
		link(2),
		datacenter(3)
	}
	MAX-ACCESS read-only
	STATUS current
	DESCRIPTION
		"The availability dependency for the specified application.
		The application object availability does not depend on anything,
		or it depends on at lease one of server, link, or data center being up."
	::= { gtmAppEntry 4 }

--==================================================================
-- Gtm_application_status
--==================================================================
gtmAppStatusNumber OBJECT-TYPE
	SYNTAX INTEGER
	MAX-ACCESS read-only
	STATUS current
	DESCRIPTION
		"The number of gtmApplicationStatus entries in the table."
	::= { gtmApplicationStatus 1 }

gtmAppStatusTable OBJECT-TYPE
	SYNTAX SEQUENCE OF GtmAppStatusEntry
	MAX-ACCESS not-accessible
	STATUS current
	DESCRIPTION
		"A table containing status information of applications for GTM (Global Traffic Management)."
	::= { gtmApplicationStatus 2 }

gtmAppStatusEntry OBJECT-TYPE
	SYNTAX  GtmAppStatusEntry
	MAX-ACCESS not-accessible
	STATUS current
	DESCRIPTION
		"Columns in the gtmAppStatus Table"
	INDEX {
		gtmAppStatusName
	}
	::= { gtmAppStatusTable 1 }

GtmAppStatusEntry ::=
	SEQUENCE {
        	gtmAppStatusName                                          LongDisplayString,
        	gtmAppStatusAvailState                                    INTEGER,
        	gtmAppStatusEnabledState                                  INTEGER,
        	gtmAppStatusParentType                                    Gauge,
        	gtmAppStatusDetailReason                                  LongDisplayString
	}

gtmAppStatusName OBJECT-TYPE
	SYNTAX LongDisplayString
	MAX-ACCESS read-only
	STATUS current
	DESCRIPTION
		"The name of an application."
	::= { gtmAppStatusEntry 1 }

gtmAppStatusAvailState OBJECT-TYPE
	SYNTAX INTEGER {
		none(0),
		green(1),
		yellow(2),
		red(3),
		blue(4),
		gray(5)
	}
	MAX-ACCESS read-only
	STATUS current
	DESCRIPTION
		"The availability of the specified application indicated by color.
		none - error;
		green - available in some capacity;
		yellow - not currently available;
		red - not available;
	        blue - availability is unknown;
	        gray - unlicensed."
	::= { gtmAppStatusEntry 2 }

gtmAppStatusEnabledState OBJECT-TYPE
	SYNTAX INTEGER {
		none(0),
		enabled(1),
		disabled(2),
		disabledbyparent(3)
	}
	MAX-ACCESS read-only
	STATUS current
	DESCRIPTION
		"The activity status of the specified application, as specified
		by the user."
	::= { gtmAppStatusEntry 3 }

gtmAppStatusParentType OBJECT-TYPE
	SYNTAX Gauge
	MAX-ACCESS read-only
	STATUS	 deprecated
	DESCRIPTION
		"Deprecated! This is an internal data.
		The type of parent object which disabled the specified application."
	::= { gtmAppStatusEntry 4 }

gtmAppStatusDetailReason OBJECT-TYPE
	SYNTAX LongDisplayString
	MAX-ACCESS read-only
	STATUS current
	DESCRIPTION
		"The detail description of the specified application's status."
	::= { gtmAppStatusEntry 5 }

--==================================================================
-- Gtm_application_context_stat
--==================================================================
gtmAppContStatNumber OBJECT-TYPE
	SYNTAX INTEGER
	MAX-ACCESS read-only
	STATUS current
	DESCRIPTION
		"The number of gtmAppContextStat entries in the table."
	::= { gtmAppContextStat 1 }

gtmAppContStatTable OBJECT-TYPE
	SYNTAX SEQUENCE OF GtmAppContStatEntry
	MAX-ACCESS not-accessible
	STATUS current
	DESCRIPTION
		"A table containing information of all able to used objects of
		application contexts for GTM (Global Traffic Management)."
	::= { gtmAppContextStat 2 }

gtmAppContStatEntry OBJECT-TYPE
	SYNTAX  GtmAppContStatEntry
	MAX-ACCESS not-accessible
	STATUS current
	DESCRIPTION
		"Columns in the gtmAppContStat Table"
	INDEX {
		gtmAppContStatAppName,
		gtmAppContStatType,
		gtmAppContStatName
	}
	::= { gtmAppContStatTable 1 }

GtmAppContStatEntry ::=
	SEQUENCE {
        	gtmAppContStatAppName                                     LongDisplayString,
        	gtmAppContStatType                                        INTEGER,
        	gtmAppContStatName                                        LongDisplayString,
        	gtmAppContStatNumAvail                                    Counter64,
        	gtmAppContStatAvailState                                  INTEGER,
        	gtmAppContStatEnabledState                                INTEGER,
        	gtmAppContStatParentType                                  Gauge,
        	gtmAppContStatDetailReason                                LongDisplayString
	}

gtmAppContStatAppName OBJECT-TYPE
	SYNTAX LongDisplayString
	MAX-ACCESS read-only
	STATUS current
	DESCRIPTION
		"The name of an application."
	::= { gtmAppContStatEntry 1 }

gtmAppContStatType OBJECT-TYPE
	SYNTAX INTEGER {
		datacenter(0),
		server(1),
		link(2)
	}
	MAX-ACCESS read-only
	STATUS current
	DESCRIPTION
		"The object type of an application's context for the specified application."
	::= { gtmAppContStatEntry 2 }

gtmAppContStatName OBJECT-TYPE
	SYNTAX LongDisplayString
	MAX-ACCESS read-only
	STATUS current
	DESCRIPTION
		"The object name of an application's context for the specified application."
	::= { gtmAppContStatEntry 3 }

gtmAppContStatNumAvail OBJECT-TYPE
	SYNTAX Counter64
	MAX-ACCESS read-only
	STATUS current
	DESCRIPTION
		"The minimum number of pool members per wide IP available
		(green + enabled) in this context."
	::= { gtmAppContStatEntry 4 }

gtmAppContStatAvailState OBJECT-TYPE
	SYNTAX INTEGER {
		none(0),
		green(1),
		yellow(2),
		red(3),
		blue(4),
		gray(5)
	}
	MAX-ACCESS read-only
	STATUS current
	DESCRIPTION
		"The availability of the specified application context indicated by color.
		none - error;
		green - available in some capacity;
		yellow - not currently available;
		red - not available;
		blue - availability is unknown;
		gray - unlicensed."
	::= { gtmAppContStatEntry 5 }

gtmAppContStatEnabledState OBJECT-TYPE
	SYNTAX INTEGER {
		none(0),
		enabled(1),
		disabled(2),
		disabledbyparent(3)
	}
	MAX-ACCESS read-only
	STATUS current
	DESCRIPTION
		"The activity status of the specified application context, as specified
		by the user."
	::= { gtmAppContStatEntry 6 }

gtmAppContStatParentType OBJECT-TYPE
	SYNTAX Gauge
	MAX-ACCESS read-only
	STATUS	 deprecated
	DESCRIPTION
		"Deprecated! This is an internal data.
		The type of parent object which disabled the specified application context."
	::= { gtmAppContStatEntry 7 }

gtmAppContStatDetailReason OBJECT-TYPE
	SYNTAX LongDisplayString
	MAX-ACCESS read-only
	STATUS current
	DESCRIPTION
		"The detail description of the specified application context 's status."
	::= { gtmAppContStatEntry 8 }

--==================================================================
-- Gtm_application_context_disable
--==================================================================
gtmAppContDisNumber OBJECT-TYPE
	SYNTAX INTEGER
	MAX-ACCESS read-only
	STATUS current
	DESCRIPTION
		"The number of gtmAppContextDisable entries in the table."
	::= { gtmAppContextDisable 1 }

gtmAppContDisTable OBJECT-TYPE
	SYNTAX SEQUENCE OF GtmAppContDisEntry
	MAX-ACCESS not-accessible
	STATUS current
	DESCRIPTION
		"A table containing information of disabled objects of application
		contexts for GTM (Global Traffic Management)."
	::= { gtmAppContextDisable 2 }

gtmAppContDisEntry OBJECT-TYPE
	SYNTAX  GtmAppContDisEntry
	MAX-ACCESS not-accessible
	STATUS current
	DESCRIPTION
		"Columns in the gtmAppContDis Table"
	INDEX {
		gtmAppContDisAppName,
		gtmAppContDisType,
		gtmAppContDisName
	}
	::= { gtmAppContDisTable 1 }

GtmAppContDisEntry ::=
	SEQUENCE {
        	gtmAppContDisAppName                                      LongDisplayString,
        	gtmAppContDisType                                         INTEGER,
        	gtmAppContDisName                                         LongDisplayString
	}

gtmAppContDisAppName OBJECT-TYPE
	SYNTAX LongDisplayString
	MAX-ACCESS read-only
	STATUS current
	DESCRIPTION
		"The name of an application."
	::= { gtmAppContDisEntry 1 }

gtmAppContDisType OBJECT-TYPE
	SYNTAX INTEGER {
		datacenter(0),
		server(1),
		link(2)
	}
	MAX-ACCESS read-only
	STATUS current
	DESCRIPTION
		"The object type of a disabled application's context for the specified application.."
	::= { gtmAppContDisEntry 2 }

gtmAppContDisName OBJECT-TYPE
	SYNTAX LongDisplayString
	MAX-ACCESS read-only
	STATUS current
	DESCRIPTION
		"The object name of a disabled application's context for the specified application."
	::= { gtmAppContDisEntry 3 }

--==================================================================
-- Gtm_dc
--==================================================================
gtmDcNumber OBJECT-TYPE
	SYNTAX INTEGER
	MAX-ACCESS read-only
	STATUS current
	DESCRIPTION
		"The number of gtmDataCenter entries in the table."
	::= { gtmDataCenter 1 }

gtmDcTable OBJECT-TYPE
	SYNTAX SEQUENCE OF GtmDcEntry
	MAX-ACCESS not-accessible
	STATUS current
	DESCRIPTION
		"A table containing information of data centers for GTM (Global Traffic Management)."
	::= { gtmDataCenter 2 }

gtmDcEntry OBJECT-TYPE
	SYNTAX  GtmDcEntry
	MAX-ACCESS not-accessible
	STATUS current
	DESCRIPTION
		"Columns in the gtmDc Table"
	INDEX {
		gtmDcName
	}
	::= { gtmDcTable 1 }

GtmDcEntry ::=
	SEQUENCE {
        	gtmDcName                                                 LongDisplayString,
        	gtmDcLocation                                             LongDisplayString,
        	gtmDcContact                                              LongDisplayString,
        	gtmDcEnabled                                              INTEGER
	}

gtmDcName OBJECT-TYPE
	SYNTAX LongDisplayString
	MAX-ACCESS read-only
	STATUS current
	DESCRIPTION
		"The name of a data center."
	::= { gtmDcEntry 1 }

gtmDcLocation OBJECT-TYPE
	SYNTAX LongDisplayString
	MAX-ACCESS read-only
	STATUS current
	DESCRIPTION
		"The location information of the specified data center."
	::= { gtmDcEntry 2 }

gtmDcContact OBJECT-TYPE
	SYNTAX LongDisplayString
	MAX-ACCESS read-only
	STATUS current
	DESCRIPTION
		"The contact information of the specified data center."
	::= { gtmDcEntry 3 }

gtmDcEnabled OBJECT-TYPE
	SYNTAX INTEGER {
		false(0),
		true(1)
	}
	MAX-ACCESS read-only
	STATUS current
	DESCRIPTION
		"The state whether the specified data center is enabled or not."
	::= { gtmDcEntry 4 }

--==================================================================
-- Gtm_dc_stat
--==================================================================
gtmDcStatResetStats OBJECT-TYPE
	SYNTAX INTEGER
	MAX-ACCESS read-write
	STATUS current
	DESCRIPTION
		"The action to reset resettable statistics data in gtmDataCenterStat.
		 Setting this value to 1 will reset statistics data.
		 Note, some statistics data may not be reset including data that are incremental counters."
	::= { gtmDataCenterStat 1 }

gtmDcStatNumber OBJECT-TYPE
	SYNTAX INTEGER
	MAX-ACCESS read-only
	STATUS current
	DESCRIPTION
		"The number of gtmDataCenterStat entries in the table."
	::= { gtmDataCenterStat 2 }

gtmDcStatTable OBJECT-TYPE
	SYNTAX SEQUENCE OF GtmDcStatEntry
	MAX-ACCESS not-accessible
	STATUS current
	DESCRIPTION
		"A table containing statistics information of data centers
		for GTM (Global Traffic Management)."
	::= { gtmDataCenterStat 3 }

gtmDcStatEntry OBJECT-TYPE
	SYNTAX  GtmDcStatEntry
	MAX-ACCESS not-accessible
	STATUS current
	DESCRIPTION
		"Columns in the gtmDcStat Table"
	INDEX {
		gtmDcStatName
	}
	::= { gtmDcStatTable 1 }

GtmDcStatEntry ::=
	SEQUENCE {
        	gtmDcStatName                                             LongDisplayString,
        	gtmDcStatCpuUsage                                         Counter64,
        	gtmDcStatMemAvail                                         Counter64,
        	gtmDcStatBitsPerSecIn                                     Counter64,
        	gtmDcStatBitsPerSecOut                                    Counter64,
        	gtmDcStatPktsPerSecIn                                     Counter64,
        	gtmDcStatPktsPerSecOut                                    Counter64,
        	gtmDcStatConnections                                      Counter64,
        	gtmDcStatConnRate                                         Counter64
	}

gtmDcStatName OBJECT-TYPE
	SYNTAX LongDisplayString
	MAX-ACCESS read-only
	STATUS current
	DESCRIPTION
		"The name of a data center."
	::= { gtmDcStatEntry 1 }

gtmDcStatCpuUsage OBJECT-TYPE
	SYNTAX Counter64
	MAX-ACCESS read-only
	STATUS current
	DESCRIPTION
		"The CPU usage in percentage for the specified data center."
	::= { gtmDcStatEntry 2 }

gtmDcStatMemAvail OBJECT-TYPE
	SYNTAX Counter64
	MAX-ACCESS read-only
	STATUS current
	DESCRIPTION
		"The memory available in bytes for the specified data center."
	::= { gtmDcStatEntry 3 }

gtmDcStatBitsPerSecIn OBJECT-TYPE
	SYNTAX Counter64
	MAX-ACCESS read-only
	STATUS current
	DESCRIPTION
		"The number of bits per second received by the specified data center."
	::= { gtmDcStatEntry 4 }

gtmDcStatBitsPerSecOut OBJECT-TYPE
	SYNTAX Counter64
	MAX-ACCESS read-only
	STATUS current
	DESCRIPTION
		"The number of bits per second sent from the specified data center."
	::= { gtmDcStatEntry 5 }

gtmDcStatPktsPerSecIn OBJECT-TYPE
	SYNTAX Counter64
	MAX-ACCESS read-only
	STATUS current
	DESCRIPTION
		"The number of packets per second received by the specified data center."
	::= { gtmDcStatEntry 6 }

gtmDcStatPktsPerSecOut OBJECT-TYPE
	SYNTAX Counter64
	MAX-ACCESS read-only
	STATUS current
	DESCRIPTION
		"The number of packets per second sent from the specified data center."
	::= { gtmDcStatEntry 7 }

gtmDcStatConnections OBJECT-TYPE
	SYNTAX Counter64
	MAX-ACCESS read-only
	STATUS current
	DESCRIPTION
		"The number of total connections to the specified data center."
	::= { gtmDcStatEntry 8 }

gtmDcStatConnRate OBJECT-TYPE
	SYNTAX Counter64
	MAX-ACCESS read-only
	STATUS	 deprecated
	DESCRIPTION
		"Deprecated! This feature has been eliminated.
		The connection rate (current connection rate/connection rate limit)
		in percentage for the specified data center."
	::= { gtmDcStatEntry 9 }

--==================================================================
-- Gtm_dc_status
--==================================================================
gtmDcStatusNumber OBJECT-TYPE
	SYNTAX INTEGER
	MAX-ACCESS read-only
	STATUS current
	DESCRIPTION
		"The number of gtmDataCenterStatus entries in the table."
	::= { gtmDataCenterStatus 1 }

gtmDcStatusTable OBJECT-TYPE
	SYNTAX SEQUENCE OF GtmDcStatusEntry
	MAX-ACCESS not-accessible
	STATUS current
	DESCRIPTION
		"A table containing status information of data centers
		for GTM (Global Traffic Management)."
	::= { gtmDataCenterStatus 2 }

gtmDcStatusEntry OBJECT-TYPE
	SYNTAX  GtmDcStatusEntry
	MAX-ACCESS not-accessible
	STATUS current
	DESCRIPTION
		"Columns in the gtmDcStatus Table"
	INDEX {
		gtmDcStatusName
	}
	::= { gtmDcStatusTable 1 }

GtmDcStatusEntry ::=
	SEQUENCE {
        	gtmDcStatusName                                           LongDisplayString,
        	gtmDcStatusAvailState                                     INTEGER,
        	gtmDcStatusEnabledState                                   INTEGER,
        	gtmDcStatusParentType                                     Gauge,
        	gtmDcStatusDetailReason                                   LongDisplayString
	}

gtmDcStatusName OBJECT-TYPE
	SYNTAX LongDisplayString
	MAX-ACCESS read-only
	STATUS current
	DESCRIPTION
		"The name of a data center."
	::= { gtmDcStatusEntry 1 }

gtmDcStatusAvailState OBJECT-TYPE
	SYNTAX INTEGER {
		none(0),
		green(1),
		yellow(2),
		red(3),
		blue(4),
		gray(5)
	}
	MAX-ACCESS read-only
	STATUS current
	DESCRIPTION
		"The availability of the specified data center indicated by color.
		none - error;
		green - available in some capacity;
		yellow - not currently available;
		red - not available;
		blue - availability is unknown;
	 	gray - unlicensed."
	::= { gtmDcStatusEntry 2 }

gtmDcStatusEnabledState OBJECT-TYPE
	SYNTAX INTEGER {
		none(0),
		enabled(1),
		disabled(2),
		disabledbyparent(3)
	}
	MAX-ACCESS read-only
	STATUS current
	DESCRIPTION
		"The activity status of the specified data center, as specified
		by the user."
	::= { gtmDcStatusEntry 3 }

gtmDcStatusParentType OBJECT-TYPE
	SYNTAX Gauge
	MAX-ACCESS read-only
	STATUS	 deprecated
	DESCRIPTION
		"Deprecated! This is an internal data.
		The type of parent object which disabled the specified data center."
	::= { gtmDcStatusEntry 4 }

gtmDcStatusDetailReason OBJECT-TYPE
	SYNTAX LongDisplayString
	MAX-ACCESS read-only
	STATUS current
	DESCRIPTION
		"The detail description of the specified data center's status."
	::= { gtmDcStatusEntry 5 }

--==================================================================
-- Gtm_ip
--==================================================================
gtmIpNumber OBJECT-TYPE
	SYNTAX INTEGER
	MAX-ACCESS read-only
	STATUS	 deprecated
	DESCRIPTION
		"Deprecated!.
		The number of gtmIp entries in the table."
	::= { gtmIp 1 }

gtmIpTable OBJECT-TYPE
	SYNTAX SEQUENCE OF GtmIpEntry
	MAX-ACCESS not-accessible
	STATUS deprecated
	DESCRIPTION
		"Deprecated! Replaced by gtmDeviceIp and gtmLinkIp tables.
		 A table containing information of IPs for GTM (Global Traffic Management)."
	::= { gtmIp 2 }

gtmIpEntry OBJECT-TYPE
	SYNTAX  GtmIpEntry
	MAX-ACCESS not-accessible
	STATUS deprecated
	DESCRIPTION
		"Columns in the gtmIp Table"
	INDEX {
		gtmIpIpType,
		gtmIpIp,
		gtmIpLinkName,
		gtmIpServerName
	}
	::= { gtmIpTable 1 }

GtmIpEntry ::=
	SEQUENCE {
        	gtmIpIpType                                               InetAddressType,
        	gtmIpIp                                                   InetAddress,
        	gtmIpLinkName                                             LongDisplayString,
        	gtmIpServerName                                           LongDisplayString,
        	gtmIpUnitId                                               Gauge,
        	gtmIpIpXlatedType                                         InetAddressType,
        	gtmIpIpXlated                                             InetAddress,
        	gtmIpDeviceName                                           LongDisplayString
	}

gtmIpIpType OBJECT-TYPE
	SYNTAX InetAddressType
	MAX-ACCESS read-only
	STATUS	 deprecated
	DESCRIPTION
		"Deprecated! The IP address type of gtmIpIp."
	::= { gtmIpEntry 1 }

gtmIpIp OBJECT-TYPE
	SYNTAX InetAddress
	MAX-ACCESS read-only
	STATUS	 deprecated
	DESCRIPTION
		"Deprecated! The IP address that belong to the specified box. It is interpreted
		within the context of a gtmIpIpType value."
	::= { gtmIpEntry 2 }

gtmIpLinkName OBJECT-TYPE
	SYNTAX LongDisplayString
	MAX-ACCESS read-only
	STATUS	 deprecated
	DESCRIPTION
		"Deprecated! The link name with which the specified IP address associates."
	::= { gtmIpEntry 3 }

gtmIpServerName OBJECT-TYPE
	SYNTAX LongDisplayString
	MAX-ACCESS read-only
	STATUS	 deprecated
	DESCRIPTION
		"Deprecated! The name of the server with which the specified IP address is associated."
	::= { gtmIpEntry 4 }

gtmIpUnitId OBJECT-TYPE
	SYNTAX Gauge
	MAX-ACCESS read-only
	STATUS	 deprecated
	DESCRIPTION
		"Deprecated!  This is replaced by device_name.
		The box ID with which the specified IP address associates."
	::= { gtmIpEntry 5 }

gtmIpIpXlatedType OBJECT-TYPE
	SYNTAX InetAddressType
	MAX-ACCESS read-only
	STATUS	 deprecated
	DESCRIPTION
		"Deprecated! The IP address type of gtmIpIpXlated."
	::= { gtmIpEntry 6 }

gtmIpIpXlated OBJECT-TYPE
	SYNTAX InetAddress
	MAX-ACCESS read-only
	STATUS	 deprecated
	DESCRIPTION
		"Deprecated! The translated address for the specified IP. It is interpreted
		within the context of a gtmIpIpXlatedType value."
	::= { gtmIpEntry 7 }

gtmIpDeviceName OBJECT-TYPE
	SYNTAX LongDisplayString
	MAX-ACCESS read-only
	STATUS	 deprecated
	DESCRIPTION
		"Deprecated! The box name with which the specified IP address associates."
	::= { gtmIpEntry 8 }

--==================================================================
-- Gtm_link
--==================================================================
gtmLinkNumber OBJECT-TYPE
	SYNTAX INTEGER
	MAX-ACCESS read-only
	STATUS current
	DESCRIPTION
		"The number of gtmLink entries in the table."
	::= { gtmLink 1 }

gtmLinkTable OBJECT-TYPE
	SYNTAX SEQUENCE OF GtmLinkEntry
	MAX-ACCESS not-accessible
	STATUS current
	DESCRIPTION
		"A table containing information of links within associated data center
		for GTM (Global Traffic Management)."
	::= { gtmLink 2 }

gtmLinkEntry OBJECT-TYPE
	SYNTAX  GtmLinkEntry
	MAX-ACCESS not-accessible
	STATUS current
	DESCRIPTION
		"Columns in the gtmLink Table"
	INDEX {
		gtmLinkName
	}
	::= { gtmLinkTable 1 }

GtmLinkEntry ::=
	SEQUENCE {
        	gtmLinkName                                               LongDisplayString,
        	gtmLinkDcName                                             LongDisplayString,
        	gtmLinkIspName                                            LongDisplayString,
        	gtmLinkUplinkAddressType                                  InetAddressType,
        	gtmLinkUplinkAddress                                      InetAddress,
        	gtmLinkLimitInCpuUsageEnabled                             INTEGER,
        	gtmLinkLimitInMemAvailEnabled                             INTEGER,
        	gtmLinkLimitInBitsPerSecEnabled                           INTEGER,
        	gtmLinkLimitInPktsPerSecEnabled                           INTEGER,
        	gtmLinkLimitInConnEnabled                                 INTEGER,
        	gtmLinkLimitInConnPerSecEnabled                           INTEGER,
        	gtmLinkLimitInCpuUsage                                    Counter64,
        	gtmLinkLimitInMemAvail                                    Counter64,
        	gtmLinkLimitInBitsPerSec                                  Counter64,
        	gtmLinkLimitInPktsPerSec                                  Counter64,
        	gtmLinkLimitInConn                                        Counter64,
        	gtmLinkLimitInConnPerSec                                  Counter64,
        	gtmLinkLimitOutCpuUsageEnabled                            INTEGER,
        	gtmLinkLimitOutMemAvailEnabled                            INTEGER,
        	gtmLinkLimitOutBitsPerSecEnabled                          INTEGER,
        	gtmLinkLimitOutPktsPerSecEnabled                          INTEGER,
        	gtmLinkLimitOutConnEnabled                                INTEGER,
        	gtmLinkLimitOutConnPerSecEnabled                          INTEGER,
        	gtmLinkLimitOutCpuUsage                                   Counter64,
        	gtmLinkLimitOutMemAvail                                   Counter64,
        	gtmLinkLimitOutBitsPerSec                                 Counter64,
        	gtmLinkLimitOutPktsPerSec                                 Counter64,
        	gtmLinkLimitOutConn                                       Counter64,
        	gtmLinkLimitOutConnPerSec                                 Counter64,
        	gtmLinkLimitTotalCpuUsageEnabled                          INTEGER,
        	gtmLinkLimitTotalMemAvailEnabled                          INTEGER,
        	gtmLinkLimitTotalBitsPerSecEnabled                        INTEGER,
        	gtmLinkLimitTotalPktsPerSecEnabled                        INTEGER,
        	gtmLinkLimitTotalConnEnabled                              INTEGER,
        	gtmLinkLimitTotalConnPerSecEnabled                        INTEGER,
        	gtmLinkLimitTotalCpuUsage                                 Counter64,
        	gtmLinkLimitTotalMemAvail                                 Counter64,
        	gtmLinkLimitTotalBitsPerSec                               Counter64,
        	gtmLinkLimitTotalPktsPerSec                               Counter64,
        	gtmLinkLimitTotalConn                                     Counter64,
        	gtmLinkLimitTotalConnPerSec                               Counter64,
        	gtmLinkMonitorRule                                        LongDisplayString,
        	gtmLinkDuplex                                             INTEGER,
        	gtmLinkEnabled                                            INTEGER,
        	gtmLinkRatio                                              Gauge,
        	gtmLinkPrepaid                                            Counter64,
        	gtmLinkPrepaidInDollars                                   Gauge,
        	gtmLinkWeightingType                                      INTEGER
	}

gtmLinkName OBJECT-TYPE
	SYNTAX LongDisplayString
	MAX-ACCESS read-only
	STATUS current
	DESCRIPTION
		"The name of a link."
	::= { gtmLinkEntry 1 }

gtmLinkDcName OBJECT-TYPE
	SYNTAX LongDisplayString
	MAX-ACCESS read-only
	STATUS current
	DESCRIPTION
		"The name of the data center associated with the specified link."
	::= { gtmLinkEntry 2 }

gtmLinkIspName OBJECT-TYPE
	SYNTAX LongDisplayString
	MAX-ACCESS read-only
	STATUS current
	DESCRIPTION
		"The ISP (Internet Service Provider) name for the specified link."
	::= { gtmLinkEntry 3 }

gtmLinkUplinkAddressType OBJECT-TYPE
	SYNTAX InetAddressType
	MAX-ACCESS read-only
	STATUS current
	DESCRIPTION
		"The IP address type of gtmLinkUplinkAddress."
	::= { gtmLinkEntry 4 }

gtmLinkUplinkAddress OBJECT-TYPE
	SYNTAX InetAddress
	MAX-ACCESS read-only
	STATUS current
	DESCRIPTION
		"The IP address on the uplink side of the router, used for SNMP
		probing only. It is interpreted within the context of an
		gtmUplinkAddressType value."
	::= { gtmLinkEntry 5 }

gtmLinkLimitInCpuUsageEnabled OBJECT-TYPE
	SYNTAX INTEGER {
		false(0),
		true(1)
	}
	MAX-ACCESS read-only
	STATUS current
	DESCRIPTION
		"The state indicating whether to set limit of CPU usage is
		enabled or not for the inbound packets of the  specified link."
	::= { gtmLinkEntry 6 }

gtmLinkLimitInMemAvailEnabled OBJECT-TYPE
	SYNTAX INTEGER {
		false(0),
		true(1)
	}
	MAX-ACCESS read-only
	STATUS current
	DESCRIPTION
		"The state indicating whether to set limit of available memory
		is enabled or not for the inbound packets of the  specified link."
	::= { gtmLinkEntry 7 }

gtmLinkLimitInBitsPerSecEnabled OBJECT-TYPE
	SYNTAX INTEGER {
		false(0),
		true(1)
	}
	MAX-ACCESS read-only
	STATUS current
	DESCRIPTION
		"The state indicating whether to limit of number of bits per second
		is enabled or not for the inbound packets of the  specified link."
	::= { gtmLinkEntry 8 }

gtmLinkLimitInPktsPerSecEnabled OBJECT-TYPE
	SYNTAX INTEGER {
		false(0),
		true(1)
	}
	MAX-ACCESS read-only
	STATUS current
	DESCRIPTION
		"The state indicating whether to set limit of number of packets
		per second is enabled or not for the inbound packets of
		the specified link."
	::= { gtmLinkEntry 9 }

gtmLinkLimitInConnEnabled OBJECT-TYPE
	SYNTAX INTEGER {
		false(0),
		true(1)
	}
	MAX-ACCESS read-only
	STATUS current
	DESCRIPTION
		"The state indicating whether to set limit of total connections
		is enabled or not for the inbound packets of the specified link."
	::= { gtmLinkEntry 10 }

gtmLinkLimitInConnPerSecEnabled OBJECT-TYPE
	SYNTAX INTEGER {
		false(0),
		true(1)
	}
	MAX-ACCESS read-only
	STATUS	 deprecated
	DESCRIPTION
		"Deprecated! This feature has been eliminated.
		The state indicating whether to set limit of connections per second
		is enabled or not for the inbound packets of the link."
	::= { gtmLinkEntry 11 }

gtmLinkLimitInCpuUsage OBJECT-TYPE
	SYNTAX Counter64
	MAX-ACCESS read-only
	STATUS current
	DESCRIPTION
		"The limit of CPU usage as a percentage for the inbound packets
		of the specified link."
	::= { gtmLinkEntry 12 }

gtmLinkLimitInMemAvail OBJECT-TYPE
	SYNTAX Counter64
	MAX-ACCESS read-only
	STATUS current
	DESCRIPTION
		"The limit of memory available in bytes for the inbound packets
		of the specified link."
	::= { gtmLinkEntry 13 }

gtmLinkLimitInBitsPerSec OBJECT-TYPE
	SYNTAX Counter64
	MAX-ACCESS read-only
	STATUS current
	DESCRIPTION
		"The limit of number of bits per second for the inbound packets
		of the specified link."
	::= { gtmLinkEntry 14 }

gtmLinkLimitInPktsPerSec OBJECT-TYPE
	SYNTAX Counter64
	MAX-ACCESS read-only
	STATUS current
	DESCRIPTION
		"The limit of number of packets per second for the inbound packets
		of the specified link."
	::= { gtmLinkEntry 15 }

gtmLinkLimitInConn OBJECT-TYPE
	SYNTAX Counter64
	MAX-ACCESS read-only
	STATUS current
	DESCRIPTION
		"The limit of total number of connections for the inbound packets
		of the specified link."
	::= { gtmLinkEntry 16 }

gtmLinkLimitInConnPerSec OBJECT-TYPE
	SYNTAX Counter64
	MAX-ACCESS read-only
	STATUS	 deprecated
	DESCRIPTION
		"Deprecated! This feature has been eliminated.
		The limit of number of connections per second for the inbound packets
		of the specified link."
	::= { gtmLinkEntry 17 }

gtmLinkLimitOutCpuUsageEnabled OBJECT-TYPE
	SYNTAX INTEGER {
		false(0),
		true(1)
	}
	MAX-ACCESS read-only
	STATUS current
	DESCRIPTION
		"The state indicating whether to set limit of CPU usage is
		enabled or not for the outbound packets of the specified link."
	::= { gtmLinkEntry 18 }

gtmLinkLimitOutMemAvailEnabled OBJECT-TYPE
	SYNTAX INTEGER {
		false(0),
		true(1)
	}
	MAX-ACCESS read-only
	STATUS current
	DESCRIPTION
		"The state indicating whether to set limit of available memory
		is enabled or not for the outbound packets of the specified link."
	::= { gtmLinkEntry 19 }

gtmLinkLimitOutBitsPerSecEnabled OBJECT-TYPE
	SYNTAX INTEGER {
		false(0),
		true(1)
	}
	MAX-ACCESS read-only
	STATUS current
	DESCRIPTION
		"The state indicating whether to limit of number of bits per second
		is enabled or not for the outbound packets of the specified link."
	::= { gtmLinkEntry 20 }

gtmLinkLimitOutPktsPerSecEnabled OBJECT-TYPE
	SYNTAX INTEGER {
		false(0),
		true(1)
	}
	MAX-ACCESS read-only
	STATUS current
	DESCRIPTION
		"The state indicating whether to set limit of number of packets
		per second is enabled or not for the outbound packets of the specified link."
	::= { gtmLinkEntry 21 }

gtmLinkLimitOutConnEnabled OBJECT-TYPE
	SYNTAX INTEGER {
		false(0),
		true(1)
	}
	MAX-ACCESS read-only
	STATUS current
	DESCRIPTION
		"The state indicating whether to set limit of total connections
		is enabled or not for the outbound packets of the specified link."
	::= { gtmLinkEntry 22 }

gtmLinkLimitOutConnPerSecEnabled OBJECT-TYPE
	SYNTAX INTEGER {
		false(0),
		true(1)
	}
	MAX-ACCESS read-only
	STATUS	 deprecated
	DESCRIPTION
		"Deprecated! This feature has been eliminated.
		The state indicating whether to set limit of connections per second
		is enabled or not for the outbound packets of the specified link."
	::= { gtmLinkEntry 23 }

gtmLinkLimitOutCpuUsage OBJECT-TYPE
	SYNTAX Counter64
	MAX-ACCESS read-only
	STATUS current
	DESCRIPTION
		"The limit of CPU usage as a percentage for the outbound packets
		of the specified link."
	::= { gtmLinkEntry 24 }

gtmLinkLimitOutMemAvail OBJECT-TYPE
	SYNTAX Counter64
	MAX-ACCESS read-only
	STATUS current
	DESCRIPTION
		"The limit of memory available in bytes for the outbound packets
		of the specified link."
	::= { gtmLinkEntry 25 }

gtmLinkLimitOutBitsPerSec OBJECT-TYPE
	SYNTAX Counter64
	MAX-ACCESS read-only
	STATUS current
	DESCRIPTION
		"The limit of number of bits per second for the outbound packets
		of the specified link."
	::= { gtmLinkEntry 26 }

gtmLinkLimitOutPktsPerSec OBJECT-TYPE
	SYNTAX Counter64
	MAX-ACCESS read-only
	STATUS current
	DESCRIPTION
		"The limit of number of packets per second for the outbound packets
		of the specified link."
	::= { gtmLinkEntry 27 }

gtmLinkLimitOutConn OBJECT-TYPE
	SYNTAX Counter64
	MAX-ACCESS read-only
	STATUS current
	DESCRIPTION
		"The limit of total number of connections for the outbound packets
		of the specified link."
	::= { gtmLinkEntry 28 }

gtmLinkLimitOutConnPerSec OBJECT-TYPE
	SYNTAX Counter64
	MAX-ACCESS read-only
	STATUS	 deprecated
	DESCRIPTION
		"Deprecated! This feature has been eliminated.
		The limit of number of connections per second for the outbound packets
		of the specified link."
	::= { gtmLinkEntry 29 }

gtmLinkLimitTotalCpuUsageEnabled OBJECT-TYPE
	SYNTAX INTEGER {
		false(0),
		true(1)
	}
	MAX-ACCESS read-only
	STATUS current
	DESCRIPTION
		"The state indicating whether to set limit of CPU usage is enabled
		or not for the total packets of the specified link."
	::= { gtmLinkEntry 30 }

gtmLinkLimitTotalMemAvailEnabled OBJECT-TYPE
	SYNTAX INTEGER {
		false(0),
		true(1)
	}
	MAX-ACCESS read-only
	STATUS current
	DESCRIPTION
		"The state indicating whether to set limit of available memory
		is enabled or not for the total packets of the specified link."
	::= { gtmLinkEntry 31 }

gtmLinkLimitTotalBitsPerSecEnabled OBJECT-TYPE
	SYNTAX INTEGER {
		false(0),
		true(1)
	}
	MAX-ACCESS read-only
	STATUS current
	DESCRIPTION
		"The state indicating whether to limit of number of bits per second
		is enabled or not for the total packets of the specified link."
	::= { gtmLinkEntry 32 }

gtmLinkLimitTotalPktsPerSecEnabled OBJECT-TYPE
	SYNTAX INTEGER {
		false(0),
		true(1)
	}
	MAX-ACCESS read-only
	STATUS current
	DESCRIPTION
		"The state indicating whether to set limit of number of packets
		per second is enabled or not for the total packets of the specified link."
	::= { gtmLinkEntry 33 }

gtmLinkLimitTotalConnEnabled OBJECT-TYPE
	SYNTAX INTEGER {
		false(0),
		true(1)
	}
	MAX-ACCESS read-only
	STATUS current
	DESCRIPTION
		"The state indicating whether to set limit of total connections
		is enabled or not for the total packets of the specified link."
	::= { gtmLinkEntry 34 }

gtmLinkLimitTotalConnPerSecEnabled OBJECT-TYPE
	SYNTAX INTEGER {
		false(0),
		true(1)
	}
	MAX-ACCESS read-only
	STATUS	 deprecated
	DESCRIPTION
		"Deprecated! This feature has been eliminated.
		The state indicating whether to set limit of connections per second
		is enabled or not for the total packets of the specified link."
	::= { gtmLinkEntry 35 }

gtmLinkLimitTotalCpuUsage OBJECT-TYPE
	SYNTAX Counter64
	MAX-ACCESS read-only
	STATUS current
	DESCRIPTION
		"The limit of CPU usage as a percentage for the total packets
		of the specified link."
	::= { gtmLinkEntry 36 }

gtmLinkLimitTotalMemAvail OBJECT-TYPE
	SYNTAX Counter64
	MAX-ACCESS read-only
	STATUS current
	DESCRIPTION
		"The limit of memory available in bytes for the total packets
		of the specified link."
	::= { gtmLinkEntry 37 }

gtmLinkLimitTotalBitsPerSec OBJECT-TYPE
	SYNTAX Counter64
	MAX-ACCESS read-only
	STATUS current
	DESCRIPTION
		"The limit of number of bits per second for the total packets
		of the specified link."
	::= { gtmLinkEntry 38 }

gtmLinkLimitTotalPktsPerSec OBJECT-TYPE
	SYNTAX Counter64
	MAX-ACCESS read-only
	STATUS current
	DESCRIPTION
		"The limit of number of packets per second for the total packets
		of the specified link."
	::= { gtmLinkEntry 39 }

gtmLinkLimitTotalConn OBJECT-TYPE
	SYNTAX Counter64
	MAX-ACCESS read-only
	STATUS current
	DESCRIPTION
		"The limit of total number of connections for the total packets
		of the specified link."
	::= { gtmLinkEntry 40 }

gtmLinkLimitTotalConnPerSec OBJECT-TYPE
	SYNTAX Counter64
	MAX-ACCESS read-only
	STATUS	 deprecated
	DESCRIPTION
		"Deprecated! This feature has been eliminated.
		The limit of number of connections per second for the total packets
		of the specified link."
	::= { gtmLinkEntry 41 }

gtmLinkMonitorRule OBJECT-TYPE
	SYNTAX LongDisplayString
	MAX-ACCESS read-only
	STATUS current
	DESCRIPTION
		"The name of the monitor rule for this link."
	::= { gtmLinkEntry 42 }

gtmLinkDuplex OBJECT-TYPE
	SYNTAX INTEGER {
		false(0),
		true(1)
	}
	MAX-ACCESS read-only
	STATUS current
	DESCRIPTION
		"The state indicating whether the specified link uses duplex for
		the specified link."
	::= { gtmLinkEntry 43 }

gtmLinkEnabled OBJECT-TYPE
	SYNTAX INTEGER {
		false(0),
		true(1)
	}
	MAX-ACCESS read-only
	STATUS current
	DESCRIPTION
		"The state indicating whether the specified link is enabled or not
		for the specified link."
	::= { gtmLinkEntry 44 }

gtmLinkRatio OBJECT-TYPE
	SYNTAX Gauge
	MAX-ACCESS read-only
	STATUS current
	DESCRIPTION
		"The ratio (in Kbps) used to load-balance the traffic for the specified link."
	::= { gtmLinkEntry 45 }

gtmLinkPrepaid OBJECT-TYPE
	SYNTAX Counter64
	MAX-ACCESS read-only
	STATUS current
	DESCRIPTION
		"Top end of prepaid bit rate the specified link."
	::= { gtmLinkEntry 46 }

gtmLinkPrepaidInDollars OBJECT-TYPE
	SYNTAX Gauge
	MAX-ACCESS read-only
	STATUS	 deprecated
	DESCRIPTION
		"Deprecated! The cost in dollars, derived from prepaid for the specified link."
	::= { gtmLinkEntry 47 }

gtmLinkWeightingType OBJECT-TYPE
	SYNTAX INTEGER {
		ratio(0),
		cost(1)
	}
	MAX-ACCESS read-only
	STATUS current
	DESCRIPTION
		"The weight type for the specified link.
		ratio - The region database based on user-defined settings;
		cost - The region database based on ACL lists."
	::= { gtmLinkEntry 48 }

--==================================================================
-- Gtm_link_cost
--==================================================================
gtmLinkCostNumber OBJECT-TYPE
	SYNTAX INTEGER
	MAX-ACCESS read-only
	STATUS current
	DESCRIPTION
		"The number of gtmLinkCost entries in the table."
	::= { gtmLinkCost 1 }

gtmLinkCostTable OBJECT-TYPE
	SYNTAX SEQUENCE OF GtmLinkCostEntry
	MAX-ACCESS not-accessible
	STATUS current
	DESCRIPTION
		"A table containing information of costs of the specified links
		for GTM (Global Traffic Management)."
	::= { gtmLinkCost 2 }

gtmLinkCostEntry OBJECT-TYPE
	SYNTAX  GtmLinkCostEntry
	MAX-ACCESS not-accessible
	STATUS current
	DESCRIPTION
		"Columns in the gtmLinkCost Table"
	INDEX {
		gtmLinkCostName,
		gtmLinkCostIndex
	}
	::= { gtmLinkCostTable 1 }

GtmLinkCostEntry ::=
	SEQUENCE {
        	gtmLinkCostName                                           LongDisplayString,
        	gtmLinkCostIndex                                          INTEGER,
        	gtmLinkCostUptoBps                                        Counter64,
        	gtmLinkCostDollarsPerMbps                                 Gauge
	}

gtmLinkCostName OBJECT-TYPE
	SYNTAX LongDisplayString
	MAX-ACCESS read-only
	STATUS current
	DESCRIPTION
		"The name of a link."
	::= { gtmLinkCostEntry 1 }

gtmLinkCostIndex OBJECT-TYPE
	SYNTAX INTEGER(0..2147483647)
	MAX-ACCESS read-only
	STATUS current
	DESCRIPTION
		"The index of cost for the specified link."
	::= { gtmLinkCostEntry 2 }

gtmLinkCostUptoBps OBJECT-TYPE
	SYNTAX Counter64
	MAX-ACCESS read-only
	STATUS current
	DESCRIPTION
		"The upper limit (bps) that defines the cost segment of the specified link."
	::= { gtmLinkCostEntry 3 }

gtmLinkCostDollarsPerMbps OBJECT-TYPE
	SYNTAX Gauge
	MAX-ACCESS read-only
	STATUS current
	DESCRIPTION
		"The dollars cost per mega byte per second, which is associated with
		the specified link cost segment."
	::= { gtmLinkCostEntry 4 }

--==================================================================
-- Gtm_link_stat
--==================================================================
gtmLinkStatResetStats OBJECT-TYPE
	SYNTAX INTEGER
	MAX-ACCESS read-write
	STATUS current
	DESCRIPTION
		"The action to reset resettable statistics data in gtmLinkStat.
		 Setting this value to 1 will reset statistics data.
		 Note, some statistics data may not be reset including data that are incremental counters."
	::= { gtmLinkStat 1 }

gtmLinkStatNumber OBJECT-TYPE
	SYNTAX INTEGER
	MAX-ACCESS read-only
	STATUS current
	DESCRIPTION
		"The number of gtmLinkStat entries in the table."
	::= { gtmLinkStat 2 }

gtmLinkStatTable OBJECT-TYPE
	SYNTAX SEQUENCE OF GtmLinkStatEntry
	MAX-ACCESS not-accessible
	STATUS current
	DESCRIPTION
		"A table containing statistic information of links within a data center."
	::= { gtmLinkStat 3 }

gtmLinkStatEntry OBJECT-TYPE
	SYNTAX  GtmLinkStatEntry
	MAX-ACCESS not-accessible
	STATUS current
	DESCRIPTION
		"Columns in the gtmLinkStat Table"
	INDEX {
		gtmLinkStatName
	}
	::= { gtmLinkStatTable 1 }

GtmLinkStatEntry ::=
	SEQUENCE {
        	gtmLinkStatName                                           LongDisplayString,
        	gtmLinkStatRate                                           Gauge,
        	gtmLinkStatRateIn                                         Gauge,
        	gtmLinkStatRateOut                                        Gauge,
        	gtmLinkStatRateNode                                       Gauge,
        	gtmLinkStatRateNodeIn                                     Gauge,
        	gtmLinkStatRateNodeOut                                    Gauge,
        	gtmLinkStatRateVses                                       Gauge,
        	gtmLinkStatRateVsesIn                                     Gauge,
        	gtmLinkStatRateVsesOut                                    Gauge,
        	gtmLinkStatLcsIn                                          Counter64,
        	gtmLinkStatLcsOut                                         Counter64,
        	gtmLinkStatPaths                                          Counter64
	}

gtmLinkStatName OBJECT-TYPE
	SYNTAX LongDisplayString
	MAX-ACCESS read-only
	STATUS current
	DESCRIPTION
		"The name of a link."
	::= { gtmLinkStatEntry 1 }

gtmLinkStatRate OBJECT-TYPE
	SYNTAX Gauge
	MAX-ACCESS read-only
	STATUS current
	DESCRIPTION
		"The current bit rate of all traffic flowing through the specified link."
	::= { gtmLinkStatEntry 2 }

gtmLinkStatRateIn OBJECT-TYPE
	SYNTAX Gauge
	MAX-ACCESS read-only
	STATUS current
	DESCRIPTION
		"The current bit rate for all inbound traffic flowing through
		the specified link."
	::= { gtmLinkStatEntry 3 }

gtmLinkStatRateOut OBJECT-TYPE
	SYNTAX Gauge
	MAX-ACCESS read-only
	STATUS current
	DESCRIPTION
		"The current bit rate for all outbound traffic flowing through
		the specified link."
	::= { gtmLinkStatEntry 4 }

gtmLinkStatRateNode OBJECT-TYPE
	SYNTAX Gauge
	MAX-ACCESS read-only
	STATUS current
	DESCRIPTION
		"The current bit rate of the traffic flowing through nodes of
		the gateway pool for the the specified link."
	::= { gtmLinkStatEntry 5 }

gtmLinkStatRateNodeIn OBJECT-TYPE
	SYNTAX Gauge
	MAX-ACCESS read-only
	STATUS current
	DESCRIPTION
		"The current bit rate of the traffic flowing inbound through nodes
		of the gateway pool for the the specified link."
	::= { gtmLinkStatEntry 6 }

gtmLinkStatRateNodeOut OBJECT-TYPE
	SYNTAX Gauge
	MAX-ACCESS read-only
	STATUS current
	DESCRIPTION
		"The current bit rate of the traffic flowing outbound through nodes
		of the gateway pool for the the specified link."
	::= { gtmLinkStatEntry 7 }

gtmLinkStatRateVses OBJECT-TYPE
	SYNTAX Gauge
	MAX-ACCESS read-only
	STATUS current
	DESCRIPTION
		"The current of bit rate of traffic flowing through
		the external virtual server for the specified link."
	::= { gtmLinkStatEntry 8 }

gtmLinkStatRateVsesIn OBJECT-TYPE
	SYNTAX Gauge
	MAX-ACCESS read-only
	STATUS current
	DESCRIPTION
		"The current of bit rate of inbound traffic flowing through
		the external virtual server for the specified link."
	::= { gtmLinkStatEntry 9 }

gtmLinkStatRateVsesOut OBJECT-TYPE
	SYNTAX Gauge
	MAX-ACCESS read-only
	STATUS current
	DESCRIPTION
		"The current of bit rate of outbound traffic flowing through
		the external virtual server for the specified link."
	::= { gtmLinkStatEntry 10 }

gtmLinkStatLcsIn OBJECT-TYPE
	SYNTAX Counter64
	MAX-ACCESS read-only
	STATUS current
	DESCRIPTION
		"The link capacity score is used to control inbound connections
		which are load-balanced through external virtual servers which are controlled
		by GTM (Global Traffic Management) daemon."
	::= { gtmLinkStatEntry 11 }

gtmLinkStatLcsOut OBJECT-TYPE
	SYNTAX Counter64
	MAX-ACCESS read-only
	STATUS current
	DESCRIPTION
		"The link capacity score is used to set dynamic ratios on the outbound gateway
		pool members for the specified link. This controls the outbound connections."
	::= { gtmLinkStatEntry 12 }

gtmLinkStatPaths OBJECT-TYPE
	SYNTAX Counter64
	MAX-ACCESS read-only
	STATUS current
	DESCRIPTION
		"The total number of paths through the specified link."
	::= { gtmLinkStatEntry 13 }

--==================================================================
-- Gtm_link_status
--==================================================================
gtmLinkStatusNumber OBJECT-TYPE
	SYNTAX INTEGER
	MAX-ACCESS read-only
	STATUS current
	DESCRIPTION
		"The number of gtmLinkStatus entries in the table."
	::= { gtmLinkStatus 1 }

gtmLinkStatusTable OBJECT-TYPE
	SYNTAX SEQUENCE OF GtmLinkStatusEntry
	MAX-ACCESS not-accessible
	STATUS current
	DESCRIPTION
		"A table containing status information of links within a data center."
	::= { gtmLinkStatus 2 }

gtmLinkStatusEntry OBJECT-TYPE
	SYNTAX  GtmLinkStatusEntry
	MAX-ACCESS not-accessible
	STATUS current
	DESCRIPTION
		"Columns in the gtmLinkStatus Table"
	INDEX {
		gtmLinkStatusName
	}
	::= { gtmLinkStatusTable 1 }

GtmLinkStatusEntry ::=
	SEQUENCE {
        	gtmLinkStatusName                                         LongDisplayString,
        	gtmLinkStatusAvailState                                   INTEGER,
        	gtmLinkStatusEnabledState                                 INTEGER,
        	gtmLinkStatusParentType                                   Gauge,
        	gtmLinkStatusDetailReason                                 LongDisplayString
	}

gtmLinkStatusName OBJECT-TYPE
	SYNTAX LongDisplayString
	MAX-ACCESS read-only
	STATUS current
	DESCRIPTION
		"The name of a link."
	::= { gtmLinkStatusEntry 1 }

gtmLinkStatusAvailState OBJECT-TYPE
	SYNTAX INTEGER {
		none(0),
		green(1),
		yellow(2),
		red(3),
		blue(4),
		gray(5)
	}
	MAX-ACCESS read-only
	STATUS current
	DESCRIPTION
		"The availability of the specified link indicated by color.
		none - error;
		green - available in some capacity;
		yellow - not currently available;
		red - not available;
		blue - availability is unknown;
		gray - unlicensed."
	::= { gtmLinkStatusEntry 2 }

gtmLinkStatusEnabledState OBJECT-TYPE
	SYNTAX INTEGER {
		none(0),
		enabled(1),
		disabled(2),
		disabledbyparent(3)
	}
	MAX-ACCESS read-only
	STATUS current
	DESCRIPTION
		"The activity status of the specified link, as specified
		by the user."
	::= { gtmLinkStatusEntry 3 }

gtmLinkStatusParentType OBJECT-TYPE
	SYNTAX Gauge
	MAX-ACCESS read-only
	STATUS	 deprecated
	DESCRIPTION
		"Deprecated! This is an internal data.
		The type of parent object which disabled the specified link."
	::= { gtmLinkStatusEntry 4 }

gtmLinkStatusDetailReason OBJECT-TYPE
	SYNTAX LongDisplayString
	MAX-ACCESS read-only
	STATUS current
	DESCRIPTION
		"The detail description of the specified link's status."
	::= { gtmLinkStatusEntry 5 }

--==================================================================
-- Gtm_pool
--==================================================================
gtmPoolNumber OBJECT-TYPE
	SYNTAX INTEGER
	MAX-ACCESS read-only
	STATUS current
	DESCRIPTION
		"The number of gtmPool entries in the table."
	::= { gtmPool 1 }

gtmPoolTable OBJECT-TYPE
	SYNTAX SEQUENCE OF GtmPoolEntry
	MAX-ACCESS not-accessible
	STATUS current
	DESCRIPTION
		"A table containing information of pools for GTM (Global Traffic Management)."
	::= { gtmPool 2 }

gtmPoolEntry OBJECT-TYPE
	SYNTAX  GtmPoolEntry
	MAX-ACCESS not-accessible
	STATUS current
	DESCRIPTION
		"Columns in the gtmPool Table"
	INDEX {
		gtmPoolPoolType,
		gtmPoolName
	}
	::= { gtmPoolTable 1 }

GtmPoolEntry ::=
	SEQUENCE {
        	gtmPoolName                                               LongDisplayString,
        	gtmPoolTtl                                                Gauge,
        	gtmPoolEnabled                                            INTEGER,
        	gtmPoolVerifyMember                                       INTEGER,
        	gtmPoolDynamicRatio                                       INTEGER,
        	gtmPoolAnswersToReturn                                    INTEGER,
        	gtmPoolLbMode                                             INTEGER,
        	gtmPoolAlternate                                          INTEGER,
        	gtmPoolFallback                                           INTEGER,
        	gtmPoolManualResume                                       INTEGER,
        	gtmPoolQosCoeffRtt                                        Gauge,
        	gtmPoolQosCoeffHops                                       Gauge,
        	gtmPoolQosCoeffTopology                                   Gauge,
        	gtmPoolQosCoeffHitRatio                                   Gauge,
        	gtmPoolQosCoeffPacketRate                                 Gauge,
        	gtmPoolQosCoeffVsCapacity                                 Gauge,
        	gtmPoolQosCoeffBps                                        Gauge,
        	gtmPoolQosCoeffLcs                                        Gauge,
        	gtmPoolQosCoeffConnRate                                   Gauge,
        	gtmPoolFallbackIpType                                     InetAddressType,
        	gtmPoolFallbackIp                                         InetAddress,
        	gtmPoolCname                                              LongDisplayString,
        	gtmPoolLimitCpuUsageEnabled                               INTEGER,
        	gtmPoolLimitMemAvailEnabled                               INTEGER,
        	gtmPoolLimitBitsPerSecEnabled                             INTEGER,
        	gtmPoolLimitPktsPerSecEnabled                             INTEGER,
        	gtmPoolLimitConnEnabled                                   INTEGER,
        	gtmPoolLimitConnPerSecEnabled                             INTEGER,
        	gtmPoolLimitCpuUsage                                      Counter64,
        	gtmPoolLimitMemAvail                                      Counter64,
        	gtmPoolLimitBitsPerSec                                    Counter64,
        	gtmPoolLimitPktsPerSec                                    Counter64,
        	gtmPoolLimitConn                                          Counter64,
        	gtmPoolLimitConnPerSec                                    Counter64,
        	gtmPoolMonitorRule                                        LongDisplayString,
        	gtmPoolQosCoeffVsScore                                    Gauge,
        	gtmPoolFallbackIpv6Type                                   InetAddressType,
        	gtmPoolFallbackIpv6                                       InetAddress,
        	gtmPoolPoolType                                           INTEGER
	}

gtmPoolName OBJECT-TYPE
	SYNTAX LongDisplayString
	MAX-ACCESS read-only
	STATUS current
	DESCRIPTION
		"The name of a pool."
	::= { gtmPoolEntry 1 }

gtmPoolTtl OBJECT-TYPE
	SYNTAX Gauge
	MAX-ACCESS read-only
	STATUS current
	DESCRIPTION
		"The TTL value for the specified pool."
	::= { gtmPoolEntry 2 }

gtmPoolEnabled OBJECT-TYPE
	SYNTAX INTEGER {
		false(0),
		true(1)
	}
	MAX-ACCESS read-only
	STATUS current
	DESCRIPTION
		"The state indicating whether the specified pool is enabled or not."
	::= { gtmPoolEntry 3 }

gtmPoolVerifyMember OBJECT-TYPE
	SYNTAX INTEGER {
		false(0),
		true(1)
	}
	MAX-ACCESS read-only
	STATUS current
	DESCRIPTION
		"The state indicating whether or not to verify pool member availability before using it."
	::= { gtmPoolEntry 4 }

gtmPoolDynamicRatio OBJECT-TYPE
	SYNTAX INTEGER {
		false(0),
		true(1)
	}
	MAX-ACCESS read-only
	STATUS current
	DESCRIPTION
		"The state indicating whether or not to use dynamic ratio to modify
		the behavior of QOS (Quality Of Service) for the specified pool."
	::= { gtmPoolEntry 5 }

gtmPoolAnswersToReturn OBJECT-TYPE
	SYNTAX INTEGER
	MAX-ACCESS read-only
	STATUS current
	DESCRIPTION
		"The number of answers to return for a given request from the
	        specified pool. A maximum of up to 16 answers is allowed."
	::= { gtmPoolEntry 6 }

gtmPoolLbMode OBJECT-TYPE
	SYNTAX INTEGER {
		returntodns(0),
		null(1),
		roundrobin(2),
		ratio(3),
		topology(4),
		statpersit(5),
		ga(6),
		vscapacity(7),
		leastconn(8),
		lowestrtt(9),
		lowesthops(10),
		packetrate(11),
		cpu(12),
		hitratio(13),
		qos(14),
		bps(15),
		droppacket(16),
		explicitip(17),
		vsscore(18)
	}
	MAX-ACCESS read-only
	STATUS current
	DESCRIPTION
		"The preferred load balancing method for the specified pool."
	::= { gtmPoolEntry 7 }

gtmPoolAlternate OBJECT-TYPE
	SYNTAX INTEGER {
		returntodns(0),
		null(1),
		roundrobin(2),
		ratio(3),
		topology(4),
		statpersit(5),
		ga(6),
		vscapacity(7),
		leastconn(8),
		lowestrtt(9),
		lowesthops(10),
		packetrate(11),
		cpu(12),
		hitratio(13),
		qos(14),
		bps(15),
		droppacket(16),
		explicitip(17),
		vsscore(18)
	}
	MAX-ACCESS read-only
	STATUS current
	DESCRIPTION
		"The alternate load balancing method for the specified pool."
	::= { gtmPoolEntry 8 }

gtmPoolFallback OBJECT-TYPE
	SYNTAX INTEGER {
		returntodns(0),
		null(1),
		roundrobin(2),
		ratio(3),
		topology(4),
		statpersit(5),
		ga(6),
		vscapacity(7),
		leastconn(8),
		lowestrtt(9),
		lowesthops(10),
		packetrate(11),
		cpu(12),
		hitratio(13),
		qos(14),
		bps(15),
		droppacket(16),
		explicitip(17),
		vsscore(18)
	}
	MAX-ACCESS read-only
	STATUS current
	DESCRIPTION
		"The fallback load balancing method for the specified pool."
	::= { gtmPoolEntry 9 }

gtmPoolManualResume OBJECT-TYPE
	SYNTAX INTEGER {
		disable(0),
		enable(1)
	}
	MAX-ACCESS read-only
	STATUS current
	DESCRIPTION
		"The state indicating whether or not to disable pool member
		when the pool member status goes from Green to Red."
	::= { gtmPoolEntry 10 }

gtmPoolQosCoeffRtt OBJECT-TYPE
	SYNTAX Gauge
	MAX-ACCESS read-only
	STATUS current
	DESCRIPTION
		"The round trip time QOS coefficient for the specified pool."
	::= { gtmPoolEntry 11 }

gtmPoolQosCoeffHops OBJECT-TYPE
	SYNTAX Gauge
	MAX-ACCESS read-only
	STATUS current
	DESCRIPTION
		"The hop count QOS coefficient for the specified pool."
	::= { gtmPoolEntry 12 }

gtmPoolQosCoeffTopology OBJECT-TYPE
	SYNTAX Gauge
	MAX-ACCESS read-only
	STATUS current
	DESCRIPTION
		"The topology QOS coefficient for the specified pool"
	::= { gtmPoolEntry 13 }

gtmPoolQosCoeffHitRatio OBJECT-TYPE
	SYNTAX Gauge
	MAX-ACCESS read-only
	STATUS current
	DESCRIPTION
		"The ping packet completion rate QOS coefficient for the specified pool."
	::= { gtmPoolEntry 14 }

gtmPoolQosCoeffPacketRate OBJECT-TYPE
	SYNTAX Gauge
	MAX-ACCESS read-only
	STATUS current
	DESCRIPTION
		"The packet rate QOS coefficient for the specified pool."
	::= { gtmPoolEntry 15 }

gtmPoolQosCoeffVsCapacity OBJECT-TYPE
	SYNTAX Gauge
	MAX-ACCESS read-only
	STATUS current
	DESCRIPTION
		"The virtual server capacity QOS coefficient for the specified pool."
	::= { gtmPoolEntry 16 }

gtmPoolQosCoeffBps OBJECT-TYPE
	SYNTAX Gauge
	MAX-ACCESS read-only
	STATUS current
	DESCRIPTION
		"The bandwidth QOS coefficient for the specified pool."
	::= { gtmPoolEntry 17 }

gtmPoolQosCoeffLcs OBJECT-TYPE
	SYNTAX Gauge
	MAX-ACCESS read-only
	STATUS current
	DESCRIPTION
		"The link capacity QOS coefficient for the specified pool."
	::= { gtmPoolEntry 18 }

gtmPoolQosCoeffConnRate OBJECT-TYPE
	SYNTAX Gauge
	MAX-ACCESS read-only
	STATUS	 deprecated
	DESCRIPTION
		"Deprecated!
		Replaced by gtmPoolQosCoeffVsScore.
		The connection rate QOS coefficient for the specified pool."
	::= { gtmPoolEntry 19 }

gtmPoolFallbackIpType OBJECT-TYPE
	SYNTAX InetAddressType
	MAX-ACCESS read-only
	STATUS current
	DESCRIPTION
		"The IP address type of gtmPoolFallbackIp. This field is used
	        to store the IPv4 fallback IP address type for A type pools and
	        the IPv6 fallback IP address type for AAAA type pools."
	::= { gtmPoolEntry 20 }

gtmPoolFallbackIp OBJECT-TYPE
	SYNTAX InetAddress
	MAX-ACCESS read-only
	STATUS current
	DESCRIPTION
		"The fallback/emergency failure IP for the specified pool. It is
		interpreted within the context of a gtmPoolFallbackIpType value.
	        This field is used to store the IPv4 fallback IP address for A type
	        pools and the IPv6 fallback IP address for AAAA type pools."
	::= { gtmPoolEntry 21 }

gtmPoolCname OBJECT-TYPE
	SYNTAX LongDisplayString
	MAX-ACCESS read-only
	STATUS	 deprecated
	DESCRIPTION
		"Deprecated! No longer used. To achieve similar behavior please use
	        a CNAME type pool member with static target setting enabled.
	        The CNAME (canonical name) for the specified pool. CNAME is also
	        referred to as a CNAME record, a record in a DNS database that
	        indicates the true, or canonical, host name of a computer that its
	        aliases are associated with. (eg. www.wip.d.com)."
	::= { gtmPoolEntry 22 }

gtmPoolLimitCpuUsageEnabled OBJECT-TYPE
	SYNTAX INTEGER {
		false(0),
		true(1)
	}
	MAX-ACCESS read-only
	STATUS current
	DESCRIPTION
		"The state indicating whether to set limit of CPU usage is enabled
		or not for the specified pool."
	::= { gtmPoolEntry 23 }

gtmPoolLimitMemAvailEnabled OBJECT-TYPE
	SYNTAX INTEGER {
		false(0),
		true(1)
	}
	MAX-ACCESS read-only
	STATUS current
	DESCRIPTION
		"The state indicating whether to set limit of available memory
		is enabled or not for the specified pool."
	::= { gtmPoolEntry 24 }

gtmPoolLimitBitsPerSecEnabled OBJECT-TYPE
	SYNTAX INTEGER {
		false(0),
		true(1)
	}
	MAX-ACCESS read-only
	STATUS current
	DESCRIPTION
		"The state indicating whether to limit of number of bits per second
		is enabled or not for the specified pool."
	::= { gtmPoolEntry 25 }

gtmPoolLimitPktsPerSecEnabled OBJECT-TYPE
	SYNTAX INTEGER {
		false(0),
		true(1)
	}
	MAX-ACCESS read-only
	STATUS current
	DESCRIPTION
		"The state indicating whether to set limit of number of packets
		per second is enabled or not for the specified pool."
	::= { gtmPoolEntry 26 }

gtmPoolLimitConnEnabled OBJECT-TYPE
	SYNTAX INTEGER {
		false(0),
		true(1)
	}
	MAX-ACCESS read-only
	STATUS current
	DESCRIPTION
		"The state indicating whether to set limit of total connections
		is enabled or not for the specified pool."
	::= { gtmPoolEntry 27 }

gtmPoolLimitConnPerSecEnabled OBJECT-TYPE
	SYNTAX INTEGER {
		false(0),
		true(1)
	}
	MAX-ACCESS read-only
	STATUS	 deprecated
	DESCRIPTION
		"Deprecated! This feature has been eliminated.
		The state indicating whether to set limit of connections per second
		is enabled or not for the specified pool."
	::= { gtmPoolEntry 28 }

gtmPoolLimitCpuUsage OBJECT-TYPE
	SYNTAX Counter64
	MAX-ACCESS read-only
	STATUS current
	DESCRIPTION
		"The limit of CPU usage as a percentage for the specified pool."
	::= { gtmPoolEntry 29 }

gtmPoolLimitMemAvail OBJECT-TYPE
	SYNTAX Counter64
	MAX-ACCESS read-only
	STATUS current
	DESCRIPTION
		"The limit of memory available in bytes for the specified pool."
	::= { gtmPoolEntry 30 }

gtmPoolLimitBitsPerSec OBJECT-TYPE
	SYNTAX Counter64
	MAX-ACCESS read-only
	STATUS current
	DESCRIPTION
		"The limit of number of bits per second for the specified pool."
	::= { gtmPoolEntry 31 }

gtmPoolLimitPktsPerSec OBJECT-TYPE
	SYNTAX Counter64
	MAX-ACCESS read-only
	STATUS current
	DESCRIPTION
		"The limit of number of packets per second for the specified pool."
	::= { gtmPoolEntry 32 }

gtmPoolLimitConn OBJECT-TYPE
	SYNTAX Counter64
	MAX-ACCESS read-only
	STATUS current
	DESCRIPTION
		"The limit of total number of connections for the specified pool."
	::= { gtmPoolEntry 33 }

gtmPoolLimitConnPerSec OBJECT-TYPE
	SYNTAX Counter64
	MAX-ACCESS read-only
	STATUS	 deprecated
	DESCRIPTION
		"Deprecated! This feature has been eliminated.
		The limit of number of connections per second for the specified pool."
	::= { gtmPoolEntry 34 }

gtmPoolMonitorRule OBJECT-TYPE
	SYNTAX LongDisplayString
	MAX-ACCESS read-only
	STATUS current
	DESCRIPTION
		"The monitor rule used by the specified pool."
	::= { gtmPoolEntry 35 }

gtmPoolQosCoeffVsScore OBJECT-TYPE
	SYNTAX Gauge
	MAX-ACCESS read-only
	STATUS current
	DESCRIPTION
		"The relative weight for virtual server (VS) score
		when the load balancing mode is set to LB_METHOD_QOS for the specified pool."
	::= { gtmPoolEntry 36 }

gtmPoolFallbackIpv6Type OBJECT-TYPE
	SYNTAX InetAddressType
	MAX-ACCESS read-only
	STATUS	 deprecated
	DESCRIPTION
		"Deprecated! No longer used. Please use gtmPoolFallbackIpType as this
	        field is used to store the IPv4 fallback IP address type for A type
	        pools and the IPv6 fallback IP address type for AAAA type pools.
	        The IP address type of gtmPoolFallbackIpv6."
	::= { gtmPoolEntry 37 }

gtmPoolFallbackIpv6 OBJECT-TYPE
	SYNTAX InetAddress
	MAX-ACCESS read-only
	STATUS	 deprecated
	DESCRIPTION
		"Deprecated! No longer used. Please use gtmPoolFallbackIp as this
	        field is used to store the IPv4 fallback IP address for A type pools
	        and the IPv6 fallback IP address for AAAA type pools.
		The fallback/emergency failure IPv6 IP address for the specified pool. It is
		interpreted within the context of a gtmPoolFallbackIpv6Type value."
	::= { gtmPoolEntry 38 }

gtmPoolPoolType OBJECT-TYPE
	SYNTAX INTEGER {
		a(1),
		cname(5),
		mx(15),
		aaaa(28),
		srv(33),
		naptr(35)
	}
	MAX-ACCESS read-only
	STATUS current
	DESCRIPTION
		"The type of a pool."
	::= { gtmPoolEntry 39 }

--==================================================================
-- Gtm_pool_stat
--==================================================================
gtmPoolStatResetStats OBJECT-TYPE
	SYNTAX INTEGER
	MAX-ACCESS read-write
	STATUS current
	DESCRIPTION
		"The action to reset resettable statistics data in gtmPoolStat.
		 Setting this value to 1 will reset statistics data.
		 Note, some statistics data may not be reset including data that are incremental counters."
	::= { gtmPoolStat 1 }

gtmPoolStatNumber OBJECT-TYPE
	SYNTAX INTEGER
	MAX-ACCESS read-only
	STATUS current
	DESCRIPTION
		"The number of gtmPoolStat entries in the table."
	::= { gtmPoolStat 2 }

gtmPoolStatTable OBJECT-TYPE
	SYNTAX SEQUENCE OF GtmPoolStatEntry
	MAX-ACCESS not-accessible
	STATUS current
	DESCRIPTION
		"A table containing statistics information of pools in the GTM (Global Traffic Management)."
	::= { gtmPoolStat 3 }

gtmPoolStatEntry OBJECT-TYPE
	SYNTAX  GtmPoolStatEntry
	MAX-ACCESS not-accessible
	STATUS current
	DESCRIPTION
		"Columns in the gtmPoolStat Table"
	INDEX {
		gtmPoolStatName,
		gtmPoolStatPoolType
	}
	::= { gtmPoolStatTable 1 }

GtmPoolStatEntry ::=
	SEQUENCE {
        	gtmPoolStatName                                           LongDisplayString,
        	gtmPoolStatPreferred                                      Counter64,
        	gtmPoolStatAlternate                                      Counter64,
        	gtmPoolStatFallback                                       Counter64,
        	gtmPoolStatDropped                                        Counter64,
        	gtmPoolStatExplicitIp                                     Counter64,
        	gtmPoolStatReturnToDns                                    Counter64,
        	gtmPoolStatReturnFromDns                                  Counter64,
        	gtmPoolStatCnameResolutions                               Counter64,
        	gtmPoolStatPoolType                                       INTEGER
	}

gtmPoolStatName OBJECT-TYPE
	SYNTAX LongDisplayString
	MAX-ACCESS read-only
	STATUS current
	DESCRIPTION
		"The name of a pool."
	::= { gtmPoolStatEntry 1 }

gtmPoolStatPreferred OBJECT-TYPE
	SYNTAX Counter64
	MAX-ACCESS read-only
	STATUS current
	DESCRIPTION
		"The number of times which the preferred load balance method is used
		for the specified pool."
	::= { gtmPoolStatEntry 2 }

gtmPoolStatAlternate OBJECT-TYPE
	SYNTAX Counter64
	MAX-ACCESS read-only
	STATUS current
	DESCRIPTION
		"The number of times which the alternate load balance method is used
		for the specified pool."
	::= { gtmPoolStatEntry 3 }

gtmPoolStatFallback OBJECT-TYPE
	SYNTAX Counter64
	MAX-ACCESS read-only
	STATUS current
	DESCRIPTION
		"The number of times which the fallback load balance method is used
		for the specified pool."
	::= { gtmPoolStatEntry 4 }

gtmPoolStatDropped OBJECT-TYPE
	SYNTAX Counter64
	MAX-ACCESS read-only
	STATUS current
	DESCRIPTION
		"The number of dropped DNS messages for the specified pool."
	::= { gtmPoolStatEntry 5 }

gtmPoolStatExplicitIp OBJECT-TYPE
	SYNTAX Counter64
	MAX-ACCESS read-only
	STATUS	 deprecated
	DESCRIPTION
		"Deprecated! The number of times which a LDNS  was persisted to the
	        specified pool by the explicit IP rule."
	::= { gtmPoolStatEntry 6 }

gtmPoolStatReturnToDns OBJECT-TYPE
	SYNTAX Counter64
	MAX-ACCESS read-only
	STATUS current
	DESCRIPTION
		"The number of times which a resolve was returned to DNS (for resolution)
		for the specified pool."
	::= { gtmPoolStatEntry 7 }

gtmPoolStatReturnFromDns OBJECT-TYPE
	SYNTAX Counter64
	MAX-ACCESS read-only
	STATUS current
	DESCRIPTION
		"The number of times which a resolve was returned from DNS for the
	        specified pool."
	::= { gtmPoolStatEntry 8 }

gtmPoolStatCnameResolutions OBJECT-TYPE
	SYNTAX Counter64
	MAX-ACCESS read-only
	STATUS	 deprecated
	DESCRIPTION
		"Deprecated! No longer useful.
	        The number of times which a query is resolved by the CNAME of the
	        specified pool."
	::= { gtmPoolStatEntry 9 }

gtmPoolStatPoolType OBJECT-TYPE
	SYNTAX INTEGER {
		a(1),
		cname(5),
		mx(15),
		aaaa(28),
		srv(33),
		naptr(35)
	}
	MAX-ACCESS read-only
	STATUS current
	DESCRIPTION
		"The type of a pool."
	::= { gtmPoolStatEntry 10 }

--==================================================================
-- Gtm_pool_member
--==================================================================
gtmPoolMbrNumber OBJECT-TYPE
	SYNTAX INTEGER
	MAX-ACCESS read-only
	STATUS current
	DESCRIPTION
		"The number of gtmPoolMember entries in the table."
	::= { gtmPoolMember 1 }

gtmPoolMbrTable OBJECT-TYPE
	SYNTAX SEQUENCE OF GtmPoolMbrEntry
	MAX-ACCESS not-accessible
	STATUS current
	DESCRIPTION
		"A table containing information of pool members for GTM (Global Traffic Management)."
	::= { gtmPoolMember 2 }

gtmPoolMbrEntry OBJECT-TYPE
	SYNTAX  GtmPoolMbrEntry
	MAX-ACCESS not-accessible
	STATUS current
	DESCRIPTION
		"Columns in the gtmPoolMbr Table"
	INDEX {
		gtmPoolMbrPoolType,
		gtmPoolMbrPoolName,
		gtmPoolMbrServerName,
		gtmPoolMbrVsName
	}
	::= { gtmPoolMbrTable 1 }

GtmPoolMbrEntry ::=
	SEQUENCE {
        	gtmPoolMbrPoolName                                        LongDisplayString,
        	gtmPoolMbrIpType                                          InetAddressType,
        	gtmPoolMbrIp                                              InetAddress,
        	gtmPoolMbrPort                                            InetPortNumber,
        	gtmPoolMbrVsName                                          LongDisplayString,
        	gtmPoolMbrOrder                                           INTEGER,
        	gtmPoolMbrLimitCpuUsageEnabled                            INTEGER,
        	gtmPoolMbrLimitMemAvailEnabled                            INTEGER,
        	gtmPoolMbrLimitBitsPerSecEnabled                          INTEGER,
        	gtmPoolMbrLimitPktsPerSecEnabled                          INTEGER,
        	gtmPoolMbrLimitConnEnabled                                INTEGER,
        	gtmPoolMbrLimitConnPerSecEnabled                          INTEGER,
        	gtmPoolMbrLimitCpuUsage                                   Counter64,
        	gtmPoolMbrLimitMemAvail                                   Counter64,
        	gtmPoolMbrLimitBitsPerSec                                 Counter64,
        	gtmPoolMbrLimitPktsPerSec                                 Counter64,
        	gtmPoolMbrLimitConn                                       Counter64,
        	gtmPoolMbrLimitConnPerSec                                 Counter64,
        	gtmPoolMbrMonitorRule                                     LongDisplayString,
        	gtmPoolMbrEnabled                                         INTEGER,
        	gtmPoolMbrRatio                                           INTEGER,
        	gtmPoolMbrServerName                                      LongDisplayString,
        	gtmPoolMbrPoolType                                        INTEGER,
        	gtmPoolMbrStaticTarget                                    INTEGER,
        	gtmPoolMbrRdataPriority                                   INTEGER,
        	gtmPoolMbrRdataWeight                                     INTEGER,
        	gtmPoolMbrRdataPort                                       INTEGER,
        	gtmPoolMbrRdataOrder                                      INTEGER,
        	gtmPoolMbrRdataPreference                                 INTEGER,
        	gtmPoolMbrRdataFlags                                      LongDisplayString,
        	gtmPoolMbrRdataService                                    LongDisplayString
	}

gtmPoolMbrPoolName OBJECT-TYPE
	SYNTAX LongDisplayString
	MAX-ACCESS read-only
	STATUS current
	DESCRIPTION
		"The name of the pool to which the specified member belongs."
	::= { gtmPoolMbrEntry 1 }

gtmPoolMbrIpType OBJECT-TYPE
	SYNTAX InetAddressType
	MAX-ACCESS read-only
	STATUS	 deprecated
	DESCRIPTION
		"Deprecated! use server_name and vs_name instead,
		The IP address type of gtmPoolMemberIp."
	::= { gtmPoolMbrEntry 2 }

gtmPoolMbrIp OBJECT-TYPE
	SYNTAX InetAddress
	MAX-ACCESS read-only
	STATUS	 deprecated
	DESCRIPTION
		"Deprecated! use server_name and vs_name instead,
		The IP address of a pool member. It is interpreted within
	        the context of gtmPoolMemberIpType value."
	::= { gtmPoolMbrEntry 3 }

gtmPoolMbrPort OBJECT-TYPE
	SYNTAX InetPortNumber
	MAX-ACCESS read-only
	STATUS	 deprecated
	DESCRIPTION
		"Deprecated! use server_name and vs_name instead,
	 	The port of a pool member."
	::= { gtmPoolMbrEntry 4 }

gtmPoolMbrVsName OBJECT-TYPE
	SYNTAX LongDisplayString
	MAX-ACCESS read-only
	STATUS current
	DESCRIPTION
		"The name of the virtual server with which the specified pool member
		is associated."
	::= { gtmPoolMbrEntry 5 }

gtmPoolMbrOrder OBJECT-TYPE
	SYNTAX INTEGER
	MAX-ACCESS read-only
	STATUS current
	DESCRIPTION
		"The order of the specified pool member in the associated pool.
		It is zero-based."
	::= { gtmPoolMbrEntry 6 }

gtmPoolMbrLimitCpuUsageEnabled OBJECT-TYPE
	SYNTAX INTEGER {
		false(0),
		true(1)
	}
	MAX-ACCESS read-only
	STATUS current
	DESCRIPTION
		"The state indicating whether to set limit of CPU usage is enabled
		or not for the specified pool member."
	::= { gtmPoolMbrEntry 7 }

gtmPoolMbrLimitMemAvailEnabled OBJECT-TYPE
	SYNTAX INTEGER {
		false(0),
		true(1)
	}
	MAX-ACCESS read-only
	STATUS current
	DESCRIPTION
		"The state indicating whether or not to set limit of available memory
		is enabled for the specified pool member."
	::= { gtmPoolMbrEntry 8 }

gtmPoolMbrLimitBitsPerSecEnabled OBJECT-TYPE
	SYNTAX INTEGER {
		false(0),
		true(1)
	}
	MAX-ACCESS read-only
	STATUS current
	DESCRIPTION
		"The state indicating whether or not to limit of number of bits per
		second is enabled  for the specified pool member."
	::= { gtmPoolMbrEntry 9 }

gtmPoolMbrLimitPktsPerSecEnabled OBJECT-TYPE
	SYNTAX INTEGER {
		false(0),
		true(1)
	}
	MAX-ACCESS read-only
	STATUS current
	DESCRIPTION
		"The state indicating whether or not to set limit of number of packets
		per second is enabled for the specified pool member."
	::= { gtmPoolMbrEntry 10 }

gtmPoolMbrLimitConnEnabled OBJECT-TYPE
	SYNTAX INTEGER {
		false(0),
		true(1)
	}
	MAX-ACCESS read-only
	STATUS current
	DESCRIPTION
		"The state indicating whether or not to set limit of total connections
		is enabled  for the specified pool member."
	::= { gtmPoolMbrEntry 11 }

gtmPoolMbrLimitConnPerSecEnabled OBJECT-TYPE
	SYNTAX INTEGER {
		false(0),
		true(1)
	}
	MAX-ACCESS read-only
	STATUS	 deprecated
	DESCRIPTION
		"Deprecated! This feature has been eliminated.
		The state indicating whether or not to set limit of connections
		per second is enabled for the specified pool member."
	::= { gtmPoolMbrEntry 12 }

gtmPoolMbrLimitCpuUsage OBJECT-TYPE
	SYNTAX Counter64
	MAX-ACCESS read-only
	STATUS current
	DESCRIPTION
		"The limit of CPU usage as a percentage for the specified pool member."
	::= { gtmPoolMbrEntry 13 }

gtmPoolMbrLimitMemAvail OBJECT-TYPE
	SYNTAX Counter64
	MAX-ACCESS read-only
	STATUS current
	DESCRIPTION
		"The limit of memory available in bytes for the specified pool member."
	::= { gtmPoolMbrEntry 14 }

gtmPoolMbrLimitBitsPerSec OBJECT-TYPE
	SYNTAX Counter64
	MAX-ACCESS read-only
	STATUS current
	DESCRIPTION
		"The limit of number of bits per second for the specified pool member."
	::= { gtmPoolMbrEntry 15 }

gtmPoolMbrLimitPktsPerSec OBJECT-TYPE
	SYNTAX Counter64
	MAX-ACCESS read-only
	STATUS current
	DESCRIPTION
		"The limit of number of packets per second for the specified pool member."
	::= { gtmPoolMbrEntry 16 }

gtmPoolMbrLimitConn OBJECT-TYPE
	SYNTAX Counter64
	MAX-ACCESS read-only
	STATUS current
	DESCRIPTION
		"The limit of total number of connections for the specified pool member."
	::= { gtmPoolMbrEntry 17 }

gtmPoolMbrLimitConnPerSec OBJECT-TYPE
	SYNTAX Counter64
	MAX-ACCESS read-only
	STATUS	 deprecated
	DESCRIPTION
		"Deprecated! This feature has been eliminated.
		The limit of number of connections per second for the specified pool member."
	::= { gtmPoolMbrEntry 18 }

gtmPoolMbrMonitorRule OBJECT-TYPE
	SYNTAX LongDisplayString
	MAX-ACCESS read-only
	STATUS current
	DESCRIPTION
		"The monitor rule used by the specified pool member."
	::= { gtmPoolMbrEntry 19 }

gtmPoolMbrEnabled OBJECT-TYPE
	SYNTAX INTEGER {
		disable(0),
		enable(1)
	}
	MAX-ACCESS read-only
	STATUS current
	DESCRIPTION
		"The state indicating whether the specified pool member is enabled or not."
	::= { gtmPoolMbrEntry 20 }

gtmPoolMbrRatio OBJECT-TYPE
	SYNTAX INTEGER
	MAX-ACCESS read-only
	STATUS current
	DESCRIPTION
		"The pool member ratio."
	::= { gtmPoolMbrEntry 21 }

gtmPoolMbrServerName OBJECT-TYPE
	SYNTAX LongDisplayString
	MAX-ACCESS read-only
	STATUS current
	DESCRIPTION
		"The name of the server with which the specified pool_member is associated."
	::= { gtmPoolMbrEntry 22 }

gtmPoolMbrPoolType OBJECT-TYPE
	SYNTAX INTEGER {
		a(1),
		cname(5),
		mx(15),
		aaaa(28),
		srv(33),
		naptr(35)
	}
	MAX-ACCESS read-only
	STATUS current
	DESCRIPTION
		"The type of the pool to which the specified member belongs."
	::= { gtmPoolMbrEntry 23 }

gtmPoolMbrStaticTarget OBJECT-TYPE
	SYNTAX INTEGER {
		false(0),
		true(1)
	}
	MAX-ACCESS read-only
	STATUS current
	DESCRIPTION
		"The state indicating whether or not the pool member is a
	        static target CNAME. The default is false. This is only used
	        on CNAME type pool members."
	::= { gtmPoolMbrEntry 24 }

gtmPoolMbrRdataPriority OBJECT-TYPE
	SYNTAX INTEGER
	MAX-ACCESS read-only
	STATUS current
	DESCRIPTION
		"The pool member RDATA priority. The default is 10. This is
	        only used on MX or SRV type pool members."
	::= { gtmPoolMbrEntry 25 }

gtmPoolMbrRdataWeight OBJECT-TYPE
	SYNTAX INTEGER
	MAX-ACCESS read-only
	STATUS current
	DESCRIPTION
		"The pool member RDATA weight. The default is 10. This is
	        only used on SRV type pool members."
	::= { gtmPoolMbrEntry 26 }

gtmPoolMbrRdataPort OBJECT-TYPE
	SYNTAX INTEGER
	MAX-ACCESS read-only
	STATUS current
	DESCRIPTION
		"The pool member RDATA port. The default is 0. This is only
	        used on SRV type pool members."
	::= { gtmPoolMbrEntry 27 }

gtmPoolMbrRdataOrder OBJECT-TYPE
	SYNTAX INTEGER
	MAX-ACCESS read-only
	STATUS current
	DESCRIPTION
		"The pool member RDATA order. The default is 10. This is only
	        used on NAPTR type pool members."
	::= { gtmPoolMbrEntry 28 }

gtmPoolMbrRdataPreference OBJECT-TYPE
	SYNTAX INTEGER
	MAX-ACCESS read-only
	STATUS current
	DESCRIPTION
		"The pool member RDATA preference. The default is 10. This is
	        only used on NAPTR type pool members."
	::= { gtmPoolMbrEntry 29 }

gtmPoolMbrRdataFlags OBJECT-TYPE
	SYNTAX LongDisplayString
	MAX-ACCESS read-only
	STATUS current
	DESCRIPTION
		"The pool member RDATA flags. If specified, valid strings are
	        either 'a' for address type or 's' for service type. This is
	        only used on NAPTR type pool members."
	::= { gtmPoolMbrEntry 30 }

gtmPoolMbrRdataService OBJECT-TYPE
	SYNTAX LongDisplayString
	MAX-ACCESS read-only
	STATUS current
	DESCRIPTION
		"The pool member RDATA service. This is only used on
	        NAPTR type pool members."
	::= { gtmPoolMbrEntry 31 }

--==================================================================
-- Gtm_pool_status
--==================================================================
gtmPoolStatusNumber OBJECT-TYPE
	SYNTAX INTEGER
	MAX-ACCESS read-only
	STATUS current
	DESCRIPTION
		"The number of gtmPoolStatus entries in the table."
	::= { gtmPoolStatus 1 }

gtmPoolStatusTable OBJECT-TYPE
	SYNTAX SEQUENCE OF GtmPoolStatusEntry
	MAX-ACCESS not-accessible
	STATUS current
	DESCRIPTION
		"A table containing status information of pools in the GTM (Global Traffic Management)."
	::= { gtmPoolStatus 2 }

gtmPoolStatusEntry OBJECT-TYPE
	SYNTAX  GtmPoolStatusEntry
	MAX-ACCESS not-accessible
	STATUS current
	DESCRIPTION
		"Columns in the gtmPoolStatus Table"
	INDEX {
		gtmPoolStatusPoolType,
		gtmPoolStatusName
	}
	::= { gtmPoolStatusTable 1 }

GtmPoolStatusEntry ::=
	SEQUENCE {
        	gtmPoolStatusName                                         LongDisplayString,
        	gtmPoolStatusAvailState                                   INTEGER,
        	gtmPoolStatusEnabledState                                 INTEGER,
        	gtmPoolStatusParentType                                   Gauge,
        	gtmPoolStatusDetailReason                                 LongDisplayString,
        	gtmPoolStatusPoolType                                     INTEGER
	}

gtmPoolStatusName OBJECT-TYPE
	SYNTAX LongDisplayString
	MAX-ACCESS read-only
	STATUS current
	DESCRIPTION
		"The name of a pool."
	::= { gtmPoolStatusEntry 1 }

gtmPoolStatusAvailState OBJECT-TYPE
	SYNTAX INTEGER {
		none(0),
		green(1),
		yellow(2),
		red(3),
		blue(4),
		gray(5)
	}
	MAX-ACCESS read-only
	STATUS current
	DESCRIPTION
		"The availability of the specified pool indicated by color.
		none - error;
		green - available in some capacity;
		yellow - not currently available;
		red - not available;
		blue - availability is unknown;
		gray - unlicensed."
	::= { gtmPoolStatusEntry 2 }

gtmPoolStatusEnabledState OBJECT-TYPE
	SYNTAX INTEGER {
		none(0),
		enabled(1),
		disabled(2),
		disabledbyparent(3)
	}
	MAX-ACCESS read-only
	STATUS current
	DESCRIPTION
		"The activity status of the specified pool, as specified
		by the user."
	::= { gtmPoolStatusEntry 3 }

gtmPoolStatusParentType OBJECT-TYPE
	SYNTAX Gauge
	MAX-ACCESS read-only
	STATUS	 deprecated
	DESCRIPTION
		"Deprecated! This is an internal data.
		The type of parent object which disabled the specified pool."
	::= { gtmPoolStatusEntry 4 }

gtmPoolStatusDetailReason OBJECT-TYPE
	SYNTAX LongDisplayString
	MAX-ACCESS read-only
	STATUS current
	DESCRIPTION
		"The detail description of the specified pool's status."
	::= { gtmPoolStatusEntry 5 }

gtmPoolStatusPoolType OBJECT-TYPE
	SYNTAX INTEGER {
		a(1),
		cname(5),
		mx(15),
		aaaa(28),
		srv(33),
		naptr(35)
	}
	MAX-ACCESS read-only
	STATUS current
	DESCRIPTION
		"The type of a pool."
	::= { gtmPoolStatusEntry 6 }

--==================================================================
-- Gtm_pool_member_depends
--==================================================================
gtmPoolMbrDepsNumber OBJECT-TYPE
	SYNTAX INTEGER
	MAX-ACCESS read-only
	STATUS current
	DESCRIPTION
		"The number of gtmPoolMemberDepends entries in the table."
	::= { gtmPoolMemberDepends 1 }

gtmPoolMbrDepsTable OBJECT-TYPE
	SYNTAX SEQUENCE OF GtmPoolMbrDepsEntry
	MAX-ACCESS not-accessible
	STATUS current
	DESCRIPTION
		"A table containing information of pool members' dependencies on virtual servers for GTM (Global Traffic Management)."
	::= { gtmPoolMemberDepends 2 }

gtmPoolMbrDepsEntry OBJECT-TYPE
	SYNTAX  GtmPoolMbrDepsEntry
	MAX-ACCESS not-accessible
	STATUS current
	DESCRIPTION
		"Columns in the gtmPoolMbrDeps Table"
	INDEX {
		gtmPoolMbrDepsServerName,
		gtmPoolMbrDepsVsName,
		gtmPoolMbrDepsPoolName,
		gtmPoolMbrDepsPoolType,
		gtmPoolMbrDepsDependServerName,
		gtmPoolMbrDepsDependVsName
	}
	::= { gtmPoolMbrDepsTable 1 }

GtmPoolMbrDepsEntry ::=
	SEQUENCE {
        	gtmPoolMbrDepsIpType                                      InetAddressType,
        	gtmPoolMbrDepsIp                                          InetAddress,
        	gtmPoolMbrDepsPort                                        InetPortNumber,
        	gtmPoolMbrDepsPoolName                                    LongDisplayString,
        	gtmPoolMbrDepsVipType                                     InetAddressType,
        	gtmPoolMbrDepsVip                                         InetAddress,
        	gtmPoolMbrDepsVport                                       InetPortNumber,
        	gtmPoolMbrDepsServerName                                  LongDisplayString,
        	gtmPoolMbrDepsVsName                                      LongDisplayString,
        	gtmPoolMbrDepsDependServerName                            LongDisplayString,
        	gtmPoolMbrDepsDependVsName                                LongDisplayString,
        	gtmPoolMbrDepsPoolType                                    INTEGER
	}

gtmPoolMbrDepsIpType OBJECT-TYPE
	SYNTAX InetAddressType
	MAX-ACCESS read-only
	STATUS	 deprecated
	DESCRIPTION
		"Deprecated! use server_name and vs_name instead,
		The IP address type of gtmPoolMbrDepsIp."
	::= { gtmPoolMbrDepsEntry 1 }

gtmPoolMbrDepsIp OBJECT-TYPE
	SYNTAX InetAddress
	MAX-ACCESS read-only
	STATUS	 deprecated
	DESCRIPTION
		"Deprecated! use server_name and vs_name instead,
		The IP address of a pool member. It is interpreted within
	        the context of gtmPoolMbrDepsIpType value."
	::= { gtmPoolMbrDepsEntry 2 }

gtmPoolMbrDepsPort OBJECT-TYPE
	SYNTAX InetPortNumber
	MAX-ACCESS read-only
	STATUS	 deprecated
	DESCRIPTION
		"Deprecated! use server_name and vs_name instead,
	 	The port of a pool member."
	::= { gtmPoolMbrDepsEntry 3 }

gtmPoolMbrDepsPoolName OBJECT-TYPE
	SYNTAX LongDisplayString
	MAX-ACCESS read-only
	STATUS current
	DESCRIPTION
		"The name of a pool to which the specified member belongs."
	::= { gtmPoolMbrDepsEntry 4 }

gtmPoolMbrDepsVipType OBJECT-TYPE
	SYNTAX InetAddressType
	MAX-ACCESS read-only
	STATUS	 deprecated
	DESCRIPTION
		"Deprecated! use depend server_name and vs_name instead,
		The IP address type of gtmPoolMbrDepsVip"
	::= { gtmPoolMbrDepsEntry 5 }

gtmPoolMbrDepsVip OBJECT-TYPE
	SYNTAX InetAddress
	MAX-ACCESS read-only
	STATUS	 deprecated
	DESCRIPTION
		"Deprecated! use depend server_name and vs_name instead,
		The IP address of a virtual server on which the specified pool member depends.
		It is interpreted within the context of gtmPoolMbrDepsVipType value."
	::= { gtmPoolMbrDepsEntry 6 }

gtmPoolMbrDepsVport OBJECT-TYPE
	SYNTAX InetPortNumber
	MAX-ACCESS read-only
	STATUS	 deprecated
	DESCRIPTION
		"Deprecated! use depend server_name and vs_name instead,
	 	The port of a virtual server on  which the specified pool member depends."
	::= { gtmPoolMbrDepsEntry 7 }

gtmPoolMbrDepsServerName OBJECT-TYPE
	SYNTAX LongDisplayString
	MAX-ACCESS read-only
	STATUS current
	DESCRIPTION
		"The name of the server with which the specified pool_member is associated."
	::= { gtmPoolMbrDepsEntry 8 }

gtmPoolMbrDepsVsName OBJECT-TYPE
	SYNTAX LongDisplayString
	MAX-ACCESS read-only
	STATUS current
	DESCRIPTION
		"The virtual server name with which the pool member associated."
	::= { gtmPoolMbrDepsEntry 9 }

gtmPoolMbrDepsDependServerName OBJECT-TYPE
	SYNTAX LongDisplayString
	MAX-ACCESS read-only
	STATUS current
	DESCRIPTION
		"The server name of a virtual server on which the specified pool member depends."
	::= { gtmPoolMbrDepsEntry 10 }

gtmPoolMbrDepsDependVsName OBJECT-TYPE
	SYNTAX LongDisplayString
	MAX-ACCESS read-only
	STATUS current
	DESCRIPTION
		"The virtual server name on which the specified pool member depends."
	::= { gtmPoolMbrDepsEntry 11 }

gtmPoolMbrDepsPoolType OBJECT-TYPE
	SYNTAX INTEGER {
		a(1),
		cname(5),
		mx(15),
		aaaa(28),
		srv(33),
		naptr(35)
	}
	MAX-ACCESS read-only
	STATUS current
	DESCRIPTION
		"The type of a pool to which the specified member belongs."
	::= { gtmPoolMbrDepsEntry 12 }

--==================================================================
-- Gtm_pool_member_stat
--==================================================================
gtmPoolMbrStatResetStats OBJECT-TYPE
	SYNTAX INTEGER
	MAX-ACCESS read-write
	STATUS current
	DESCRIPTION
		"The action to reset resettable statistics data in gtmPoolMemberStat.
		 Setting this value to 1 will reset statistics data.
		 Note, some statistics data may not be reset including data that are incremental counters."
	::= { gtmPoolMemberStat 1 }

gtmPoolMbrStatNumber OBJECT-TYPE
	SYNTAX INTEGER
	MAX-ACCESS read-only
	STATUS current
	DESCRIPTION
		"The number of gtmPoolMemberStat entries in the table."
	::= { gtmPoolMemberStat 2 }

gtmPoolMbrStatTable OBJECT-TYPE
	SYNTAX SEQUENCE OF GtmPoolMbrStatEntry
	MAX-ACCESS not-accessible
	STATUS current
	DESCRIPTION
		"A table containing statistics information of pool members for GTM (Global Traffic Management)."
	::= { gtmPoolMemberStat 3 }

gtmPoolMbrStatEntry OBJECT-TYPE
	SYNTAX  GtmPoolMbrStatEntry
	MAX-ACCESS not-accessible
	STATUS current
	DESCRIPTION
		"Columns in the gtmPoolMbrStat Table"
	INDEX {
		gtmPoolMbrStatPoolType,
		gtmPoolMbrStatPoolName,
		gtmPoolMbrStatServerName,
		gtmPoolMbrStatVsName
	}
	::= { gtmPoolMbrStatTable 1 }

GtmPoolMbrStatEntry ::=
	SEQUENCE {
        	gtmPoolMbrStatPoolName                                    LongDisplayString,
        	gtmPoolMbrStatIpType                                      InetAddressType,
        	gtmPoolMbrStatIp                                          InetAddress,
        	gtmPoolMbrStatPort                                        InetPortNumber,
        	gtmPoolMbrStatPreferred                                   Counter64,
        	gtmPoolMbrStatAlternate                                   Counter64,
        	gtmPoolMbrStatFallback                                    Counter64,
        	gtmPoolMbrStatServerName                                  LongDisplayString,
        	gtmPoolMbrStatVsName                                      LongDisplayString,
        	gtmPoolMbrStatPoolType                                    INTEGER
	}

gtmPoolMbrStatPoolName OBJECT-TYPE
	SYNTAX LongDisplayString
	MAX-ACCESS read-only
	STATUS current
	DESCRIPTION
		"The name of the parent pool to which the member belongs."
	::= { gtmPoolMbrStatEntry 1 }

gtmPoolMbrStatIpType OBJECT-TYPE
	SYNTAX InetAddressType
	MAX-ACCESS read-only
	STATUS	 deprecated
	DESCRIPTION
		"Deprecated! use server_name and vs_name instead,
		The IP address type of gtmPoolMemberStatIp."
	::= { gtmPoolMbrStatEntry 2 }

gtmPoolMbrStatIp OBJECT-TYPE
	SYNTAX InetAddress
	MAX-ACCESS read-only
	STATUS	 deprecated
	DESCRIPTION
		"Deprecated! use server_name and vs_name instead,
		The IP address of a pool member. It is interpreted within
	        the context of gtmPoolMemberStatIpType value."
	::= { gtmPoolMbrStatEntry 3 }

gtmPoolMbrStatPort OBJECT-TYPE
	SYNTAX InetPortNumber
	MAX-ACCESS read-only
	STATUS	 deprecated
	DESCRIPTION
		"Deprecated! use server_name and vs_name instead,
	 	The port of a pool member."
	::= { gtmPoolMbrStatEntry 4 }

gtmPoolMbrStatPreferred OBJECT-TYPE
	SYNTAX Counter64
	MAX-ACCESS read-only
	STATUS current
	DESCRIPTION
		"The number of times which the preferred load balance method is used
		for the specified pool member."
	::= { gtmPoolMbrStatEntry 5 }

gtmPoolMbrStatAlternate OBJECT-TYPE
	SYNTAX Counter64
	MAX-ACCESS read-only
	STATUS current
	DESCRIPTION
		"The number of times which the alternate load balance method is used
		for the specified pool member."
	::= { gtmPoolMbrStatEntry 6 }

gtmPoolMbrStatFallback OBJECT-TYPE
	SYNTAX Counter64
	MAX-ACCESS read-only
	STATUS current
	DESCRIPTION
		"The number of times which the fallback load balance method is used
		for the specified pool member."
	::= { gtmPoolMbrStatEntry 7 }

gtmPoolMbrStatServerName OBJECT-TYPE
	SYNTAX LongDisplayString
	MAX-ACCESS read-only
	STATUS current
	DESCRIPTION
		"The name of the server with which the specified pool_member is associated."
	::= { gtmPoolMbrStatEntry 8 }

gtmPoolMbrStatVsName OBJECT-TYPE
	SYNTAX LongDisplayString
	MAX-ACCESS read-only
	STATUS current
	DESCRIPTION
		"The name of the specified virtual server."
	::= { gtmPoolMbrStatEntry 9 }

gtmPoolMbrStatPoolType OBJECT-TYPE
	SYNTAX INTEGER {
		a(1),
		cname(5),
		mx(15),
		aaaa(28),
		srv(33),
		naptr(35)
	}
	MAX-ACCESS read-only
	STATUS current
	DESCRIPTION
		"The type of a pool to which the specified member belongs."
	::= { gtmPoolMbrStatEntry 10 }

--==================================================================
-- Gtm_pool_member_status
--==================================================================
gtmPoolMbrStatusNumber OBJECT-TYPE
	SYNTAX INTEGER
	MAX-ACCESS read-only
	STATUS current
	DESCRIPTION
		"The number of gtmPoolMemberStatus entries in the table."
	::= { gtmPoolMemberStatus 1 }

gtmPoolMbrStatusTable OBJECT-TYPE
	SYNTAX SEQUENCE OF GtmPoolMbrStatusEntry
	MAX-ACCESS not-accessible
	STATUS current
	DESCRIPTION
		"A table containing status information of pool members for GTM (Global Traffic Management)."
	::= { gtmPoolMemberStatus 2 }

gtmPoolMbrStatusEntry OBJECT-TYPE
	SYNTAX  GtmPoolMbrStatusEntry
	MAX-ACCESS not-accessible
	STATUS current
	DESCRIPTION
		"Columns in the gtmPoolMbrStatus Table"
	INDEX {
		gtmPoolMbrStatusPoolType,
		gtmPoolMbrStatusPoolName,
		gtmPoolMbrStatusServerName,
		gtmPoolMbrStatusVsName
	}
	::= { gtmPoolMbrStatusTable 1 }

GtmPoolMbrStatusEntry ::=
	SEQUENCE {
        	gtmPoolMbrStatusPoolName                                  LongDisplayString,
        	gtmPoolMbrStatusIpType                                    InetAddressType,
        	gtmPoolMbrStatusIp                                        InetAddress,
        	gtmPoolMbrStatusPort                                      InetPortNumber,
        	gtmPoolMbrStatusAvailState                                INTEGER,
        	gtmPoolMbrStatusEnabledState                              INTEGER,
        	gtmPoolMbrStatusParentType                                Gauge,
        	gtmPoolMbrStatusDetailReason                              LongDisplayString,
        	gtmPoolMbrStatusVsName                                    LongDisplayString,
        	gtmPoolMbrStatusServerName                                LongDisplayString,
        	gtmPoolMbrStatusPoolType                                  INTEGER
	}

gtmPoolMbrStatusPoolName OBJECT-TYPE
	SYNTAX LongDisplayString
	MAX-ACCESS read-only
	STATUS current
	DESCRIPTION
		"The name of the pool to which the specified member belongs."
	::= { gtmPoolMbrStatusEntry 1 }

gtmPoolMbrStatusIpType OBJECT-TYPE
	SYNTAX InetAddressType
	MAX-ACCESS read-only
	STATUS	 deprecated
	DESCRIPTION
		"Deprecated! use server_name and vs_name instead,
		The IP address type of gtmPoolMbrStatusIp."
	::= { gtmPoolMbrStatusEntry 2 }

gtmPoolMbrStatusIp OBJECT-TYPE
	SYNTAX InetAddress
	MAX-ACCESS read-only
	STATUS	 deprecated
	DESCRIPTION
		"Deprecated! use server_name and vs_name instead,
		The IP address of a pool member. It is interpreted within
	        the context of gtmPoolMbrStatusIpType value."
	::= { gtmPoolMbrStatusEntry 3 }

gtmPoolMbrStatusPort OBJECT-TYPE
	SYNTAX InetPortNumber
	MAX-ACCESS read-only
	STATUS	 deprecated
	DESCRIPTION
		"Deprecated! use server_name and vs_name instead,
	 	The port of a pool member."
	::= { gtmPoolMbrStatusEntry 4 }

gtmPoolMbrStatusAvailState OBJECT-TYPE
	SYNTAX INTEGER {
		none(0),
		green(1),
		yellow(2),
		red(3),
		blue(4),
		gray(5)
	}
	MAX-ACCESS read-only
	STATUS current
	DESCRIPTION
		"The availability of the specified pool member indicated by color.
		none - error;
		green - available in some capacity;
		yellow - not currently available;
		red - not available;
		blue - availability is unknown;
		gray - unlicensed."
	::= { gtmPoolMbrStatusEntry 5 }

gtmPoolMbrStatusEnabledState OBJECT-TYPE
	SYNTAX INTEGER {
		none(0),
		enabled(1),
		disabled(2),
		disabledbyparent(3)
	}
	MAX-ACCESS read-only
	STATUS current
	DESCRIPTION
		"The activity status of the specified pool member, as specified
		by the user."
	::= { gtmPoolMbrStatusEntry 6 }

gtmPoolMbrStatusParentType OBJECT-TYPE
	SYNTAX Gauge
	MAX-ACCESS read-only
	STATUS	 deprecated
	DESCRIPTION
		"Deprecated! This is an internal data.
		The type of parent object which disabled the specified pool member."
	::= { gtmPoolMbrStatusEntry 7 }

gtmPoolMbrStatusDetailReason OBJECT-TYPE
	SYNTAX LongDisplayString
	MAX-ACCESS read-only
	STATUS current
	DESCRIPTION
		"The detail description of the specified node's status."
	::= { gtmPoolMbrStatusEntry 8 }

gtmPoolMbrStatusVsName OBJECT-TYPE
	SYNTAX LongDisplayString
	MAX-ACCESS read-only
	STATUS current
	DESCRIPTION
		"The name of the virtual server with which the specified pool member
		is associated."
	::= { gtmPoolMbrStatusEntry 9 }

gtmPoolMbrStatusServerName OBJECT-TYPE
	SYNTAX LongDisplayString
	MAX-ACCESS read-only
	STATUS current
	DESCRIPTION
		"The name of the server with which the specified pool_member is associated."
	::= { gtmPoolMbrStatusEntry 10 }

gtmPoolMbrStatusPoolType OBJECT-TYPE
	SYNTAX INTEGER {
		a(1),
		cname(5),
		mx(15),
		aaaa(28),
		srv(33),
		naptr(35)
	}
	MAX-ACCESS read-only
	STATUS current
	DESCRIPTION
		"The type of the pool to which the specified member belongs."
	::= { gtmPoolMbrStatusEntry 11 }

--==================================================================
-- Gtm_region_entry
--==================================================================
gtmRegionEntryNumber OBJECT-TYPE
	SYNTAX INTEGER
	MAX-ACCESS read-only
	STATUS current
	DESCRIPTION
		"The number of gtmRegionEntry entries in the table."
	::= { gtmRegionEntry 1 }

gtmRegionEntryTable OBJECT-TYPE
	SYNTAX SEQUENCE OF GtmRegionEntryEntry
	MAX-ACCESS not-accessible
	STATUS current
	DESCRIPTION
		"A table containing information of user-defined region definitions for GTM (Global Traffic Management)."
	::= { gtmRegionEntry 2 }

gtmRegionEntryEntry OBJECT-TYPE
	SYNTAX  GtmRegionEntryEntry
	MAX-ACCESS not-accessible
	STATUS current
	DESCRIPTION
		"Columns in the gtmRegionEntry Table"
	INDEX {
		gtmRegionEntryName
	}
	::= { gtmRegionEntryTable 1 }

GtmRegionEntryEntry ::=
	SEQUENCE {
        	gtmRegionEntryName                                        LongDisplayString,
        	gtmRegionEntryRegionDbType                                INTEGER
	}

gtmRegionEntryName OBJECT-TYPE
	SYNTAX LongDisplayString
	MAX-ACCESS read-only
	STATUS current
	DESCRIPTION
		"The name of region entry."
	::= { gtmRegionEntryEntry 1 }

gtmRegionEntryRegionDbType OBJECT-TYPE
	SYNTAX INTEGER {
		user(0),
		acl(1),
		isp(2)
	}
	MAX-ACCESS read-only
	STATUS current
	DESCRIPTION
		"The region's database type."
	::= { gtmRegionEntryEntry 2 }

--==================================================================
-- Gtm_reg_item
--==================================================================
gtmRegItemNumber OBJECT-TYPE
	SYNTAX INTEGER
	MAX-ACCESS read-only
	STATUS current
	DESCRIPTION
		"The number of gtmRegItem entries in the table."
	::= { gtmRegItem 1 }

gtmRegItemTable OBJECT-TYPE
	SYNTAX SEQUENCE OF GtmRegItemEntry
	MAX-ACCESS not-accessible
	STATUS current
	DESCRIPTION
		"A table containing information of region items in associated region for GTM (Global Traffic Management)."
	::= { gtmRegItem 2 }

gtmRegItemEntry OBJECT-TYPE
	SYNTAX  GtmRegItemEntry
	MAX-ACCESS not-accessible
	STATUS current
	DESCRIPTION
		"Columns in the gtmRegItem Table"
	INDEX {
		gtmRegItemRegionDbType,
		gtmRegItemRegionName,
		gtmRegItemType,
		gtmRegItemNegate,
		gtmRegItemRegEntry
	}
	::= { gtmRegItemTable 1 }

GtmRegItemEntry ::=
	SEQUENCE {
        	gtmRegItemRegionDbType                                    INTEGER,
        	gtmRegItemRegionName                                      LongDisplayString,
        	gtmRegItemType                                            INTEGER,
        	gtmRegItemNegate                                          INTEGER,
        	gtmRegItemRegEntry                                        LongDisplayString
	}

gtmRegItemRegionDbType OBJECT-TYPE
	SYNTAX INTEGER {
		user(0),
		acl(1),
		isp(2)
	}
	MAX-ACCESS read-only
	STATUS current
	DESCRIPTION
		"The region's database type."
	::= { gtmRegItemEntry 1 }

gtmRegItemRegionName OBJECT-TYPE
	SYNTAX LongDisplayString
	MAX-ACCESS read-only
	STATUS current
	DESCRIPTION
		"The region name."
	::= { gtmRegItemEntry 2 }

gtmRegItemType OBJECT-TYPE
	SYNTAX INTEGER {
		cidr(0),
		region(1),
		continent(2),
		country(3),
		state(4),
		pool(5),
		datacenter(6),
		ispregion(7),
		geoipIsp(8)
	}
	MAX-ACCESS read-only
	STATUS current
	DESCRIPTION
		"The region item's type."
	::= { gtmRegItemEntry 3 }

gtmRegItemNegate OBJECT-TYPE
	SYNTAX INTEGER {
		false(0),
		true(1)
	}
	MAX-ACCESS read-only
	STATUS current
	DESCRIPTION
		"The state indicating whether the region member to be interpreted
		as not equal to the region member options selected."
	::= { gtmRegItemEntry 4 }

gtmRegItemRegEntry OBJECT-TYPE
	SYNTAX LongDisplayString
	MAX-ACCESS read-only
	STATUS current
	DESCRIPTION
		"The name of the region entry."
	::= { gtmRegItemEntry 5 }

--==================================================================
-- Gtm_rule
--==================================================================
gtmRuleNumber OBJECT-TYPE
	SYNTAX INTEGER
	MAX-ACCESS read-only
	STATUS current
	DESCRIPTION
		"The number of gtmRule entries in the table."
	::= { gtmRule 1 }

gtmRuleTable OBJECT-TYPE
	SYNTAX SEQUENCE OF GtmRuleEntry
	MAX-ACCESS not-accessible
	STATUS current
	DESCRIPTION
		"A table containing information of rules for GTM (Global Traffic Management)."
	::= { gtmRule 2 }

gtmRuleEntry OBJECT-TYPE
	SYNTAX  GtmRuleEntry
	MAX-ACCESS not-accessible
	STATUS current
	DESCRIPTION
		"Columns in the gtmRule Table"
	INDEX {
		gtmRuleName
	}
	::= { gtmRuleTable 1 }

GtmRuleEntry ::=
	SEQUENCE {
        	gtmRuleName                                               LongDisplayString,
        	gtmRuleDefinition                                         LongDisplayString,
        	gtmRuleConfigSource                                       INTEGER
	}

gtmRuleName OBJECT-TYPE
	SYNTAX LongDisplayString
	MAX-ACCESS read-only
	STATUS current
	DESCRIPTION
		"The name of a rule."
	::= { gtmRuleEntry 1 }

gtmRuleDefinition OBJECT-TYPE
	SYNTAX LongDisplayString
	MAX-ACCESS read-only
	STATUS	 deprecated
	DESCRIPTION
		"Deprecated!
		The definition of the specified rule."
	::= { gtmRuleEntry 2 }

gtmRuleConfigSource OBJECT-TYPE
	SYNTAX INTEGER {
		usercfg(0),
		basecfg(1)
	}
	MAX-ACCESS read-only
	STATUS current
	DESCRIPTION
		"The type of rule that the specified rule is associating with.
	        It is either a base/pre-configured rule or user defined rule."
	::= { gtmRuleEntry 3 }

--==================================================================
-- Gtm_rule_event
--==================================================================
gtmRuleEventNumber OBJECT-TYPE
	SYNTAX INTEGER
	MAX-ACCESS read-only
	STATUS current
	DESCRIPTION
		"The number of gtmRuleEvent entries in the table."
	::= { gtmRuleEvent 1 }

gtmRuleEventTable OBJECT-TYPE
	SYNTAX SEQUENCE OF GtmRuleEventEntry
	MAX-ACCESS not-accessible
	STATUS current
	DESCRIPTION
		"A table containing information of rule events for GTM (Global Traffic Management)."
	::= { gtmRuleEvent 2 }

gtmRuleEventEntry OBJECT-TYPE
	SYNTAX  GtmRuleEventEntry
	MAX-ACCESS not-accessible
	STATUS current
	DESCRIPTION
		"Columns in the gtmRuleEvent Table"
	INDEX {
		gtmRuleEventName,
		gtmRuleEventEventType,
		gtmRuleEventPriority
	}
	::= { gtmRuleEventTable 1 }

GtmRuleEventEntry ::=
	SEQUENCE {
        	gtmRuleEventName                                          LongDisplayString,
        	gtmRuleEventEventType                                     LongDisplayString,
        	gtmRuleEventPriority                                      INTEGER,
        	gtmRuleEventScript                                        LongDisplayString
	}

gtmRuleEventName OBJECT-TYPE
	SYNTAX LongDisplayString
	MAX-ACCESS read-only
	STATUS current
	DESCRIPTION
		"The name of a rule."
	::= { gtmRuleEventEntry 1 }

gtmRuleEventEventType OBJECT-TYPE
	SYNTAX LongDisplayString
	MAX-ACCESS read-only
	STATUS current
	DESCRIPTION
		"The event type for which the specified rule is used."
	::= { gtmRuleEventEntry 2 }

gtmRuleEventPriority OBJECT-TYPE
	SYNTAX INTEGER(0..32767)
	MAX-ACCESS read-only
	STATUS current
	DESCRIPTION
		"The execution priority of the specified rule event."
	::= { gtmRuleEventEntry 3 }

gtmRuleEventScript OBJECT-TYPE
	SYNTAX LongDisplayString
	MAX-ACCESS read-only
	STATUS	 deprecated
	DESCRIPTION
		"Deprecated!
		The TCL script for the specified rule event."
	::= { gtmRuleEventEntry 4 }

--==================================================================
-- Gtm_rule_stat
--==================================================================
gtmRuleEventStatResetStats OBJECT-TYPE
	SYNTAX INTEGER
	MAX-ACCESS read-write
	STATUS current
	DESCRIPTION
		"The action to reset resettable statistics data in gtmRuleEventStat.
		 Setting this value to 1 will reset statistics data.
		 Note, some statistics data may not be reset including data that are incremental counters."
	::= { gtmRuleEventStat 1 }

gtmRuleEventStatNumber OBJECT-TYPE
	SYNTAX INTEGER
	MAX-ACCESS read-only
	STATUS current
	DESCRIPTION
		"The number of gtmRuleEventStat entries in the table."
	::= { gtmRuleEventStat 2 }

gtmRuleEventStatTable OBJECT-TYPE
	SYNTAX SEQUENCE OF GtmRuleEventStatEntry
	MAX-ACCESS not-accessible
	STATUS current
	DESCRIPTION
		"A table containing statistics information of rules for GTM (Global Traffic Management)."
	::= { gtmRuleEventStat 3 }

gtmRuleEventStatEntry OBJECT-TYPE
	SYNTAX  GtmRuleEventStatEntry
	MAX-ACCESS not-accessible
	STATUS current
	DESCRIPTION
		"Columns in the gtmRuleEventStat Table"
	INDEX {
		gtmRuleEventStatName,
		gtmRuleEventStatEventType,
		gtmRuleEventStatPriority
	}
	::= { gtmRuleEventStatTable 1 }

GtmRuleEventStatEntry ::=
	SEQUENCE {
        	gtmRuleEventStatName                                      LongDisplayString,
        	gtmRuleEventStatEventType                                 LongDisplayString,
        	gtmRuleEventStatPriority                                  INTEGER,
        	gtmRuleEventStatFailures                                  Counter64,
        	gtmRuleEventStatAborts                                    Counter64,
        	gtmRuleEventStatTotalExecutions                           Counter64
	}

gtmRuleEventStatName OBJECT-TYPE
	SYNTAX LongDisplayString
	MAX-ACCESS read-only
	STATUS current
	DESCRIPTION
		"The name of the rule."
	::= { gtmRuleEventStatEntry 1 }

gtmRuleEventStatEventType OBJECT-TYPE
	SYNTAX LongDisplayString
	MAX-ACCESS read-only
	STATUS current
	DESCRIPTION
		"The event type for which the rule is used."
	::= { gtmRuleEventStatEntry 2 }

gtmRuleEventStatPriority OBJECT-TYPE
	SYNTAX INTEGER(0..32767)
	MAX-ACCESS read-only
	STATUS current
	DESCRIPTION
		"The execution priority of this rule event."
	::= { gtmRuleEventStatEntry 3 }

gtmRuleEventStatFailures OBJECT-TYPE
	SYNTAX Counter64
	MAX-ACCESS read-only
	STATUS current
	DESCRIPTION
		"The number of failures for executing this rule."
	::= { gtmRuleEventStatEntry 4 }

gtmRuleEventStatAborts OBJECT-TYPE
	SYNTAX Counter64
	MAX-ACCESS read-only
	STATUS current
	DESCRIPTION
		"The number of aborts when executing this rule."
	::= { gtmRuleEventStatEntry 5 }

gtmRuleEventStatTotalExecutions OBJECT-TYPE
	SYNTAX Counter64
	MAX-ACCESS read-only
	STATUS current
	DESCRIPTION
		"The total number of executions for this rule."
	::= { gtmRuleEventStatEntry 6 }

--==================================================================
-- Gtm_server
--==================================================================
gtmServerNumber OBJECT-TYPE
	SYNTAX INTEGER
	MAX-ACCESS read-only
	STATUS current
	DESCRIPTION
		"The number of gtmServer entries in the table."
	::= { gtmServer 1 }

gtmServerTable OBJECT-TYPE
	SYNTAX SEQUENCE OF GtmServerEntry
	MAX-ACCESS not-accessible
	STATUS current
	DESCRIPTION
		"A table containing information of servers within associated
		data center for GTM (Global Traffic Management)."
	::= { gtmServer 2 }

gtmServerEntry OBJECT-TYPE
	SYNTAX  GtmServerEntry
	MAX-ACCESS not-accessible
	STATUS current
	DESCRIPTION
		"Columns in the gtmServer Table"
	INDEX {
		gtmServerName
	}
	::= { gtmServerTable 1 }

GtmServerEntry ::=
	SEQUENCE {
        	gtmServerName                                             LongDisplayString,
        	gtmServerDcName                                           LongDisplayString,
        	gtmServerType                                             INTEGER,
        	gtmServerEnabled                                          INTEGER,
        	gtmServerLimitCpuUsageEnabled                             INTEGER,
        	gtmServerLimitMemAvailEnabled                             INTEGER,
        	gtmServerLimitBitsPerSecEnabled                           INTEGER,
        	gtmServerLimitPktsPerSecEnabled                           INTEGER,
        	gtmServerLimitConnEnabled                                 INTEGER,
        	gtmServerLimitConnPerSecEnabled                           INTEGER,
        	gtmServerLimitCpuUsage                                    Counter64,
        	gtmServerLimitMemAvail                                    Counter64,
        	gtmServerLimitBitsPerSec                                  Counter64,
        	gtmServerLimitPktsPerSec                                  Counter64,
        	gtmServerLimitConn                                        Counter64,
        	gtmServerLimitConnPerSec                                  Counter64,
        	gtmServerProberType                                       InetAddressType,
        	gtmServerProber                                           InetAddress,
        	gtmServerMonitorRule                                      LongDisplayString,
        	gtmServerAllowSvcChk                                      INTEGER,
        	gtmServerAllowPath                                        INTEGER,
        	gtmServerAllowSnmp                                        INTEGER,
        	gtmServerAutoconfState                                    INTEGER,
        	gtmServerLinkAutoconfState                                INTEGER
	}

gtmServerName OBJECT-TYPE
	SYNTAX LongDisplayString
	MAX-ACCESS read-only
	STATUS current
	DESCRIPTION
		"The name of a server."
	::= { gtmServerEntry 1 }

gtmServerDcName OBJECT-TYPE
	SYNTAX LongDisplayString
	MAX-ACCESS read-only
	STATUS current
	DESCRIPTION
		"The name of the data center the specified server belongs to."
	::= { gtmServerEntry 2 }

gtmServerType OBJECT-TYPE
	SYNTAX INTEGER {
		bigipstandalone(0),
		bigipredundant(1),
		genericloadbalancer(2),
		alteonacedirector(3),
		ciscocss(4),
		ciscolocaldirectorv2(5),
		ciscolocaldirectorv3(6),
		ciscoserverloadbalancer(7),
		extreme(8),
		foundryserveriron(9),
		generichost(10),
		cacheflow(11),
		netapp(12),
		windows2000(13),
		windowsnt4(14),
		solaris(15),
		radware(16)
	}
	MAX-ACCESS read-only
	STATUS current
	DESCRIPTION
		"The type of the server."
	::= { gtmServerEntry 3 }

gtmServerEnabled OBJECT-TYPE
	SYNTAX INTEGER {
		false(0),
		true(1)
	}
	MAX-ACCESS read-only
	STATUS current
	DESCRIPTION
		"The state indicating whether the specified server is enabled or not."
	::= { gtmServerEntry 4 }

gtmServerLimitCpuUsageEnabled OBJECT-TYPE
	SYNTAX INTEGER {
		false(0),
		true(1)
	}
	MAX-ACCESS read-only
	STATUS current
	DESCRIPTION
		"The state indicating whether to set limit of CPU usage is enabled
		or not for the server."
	::= { gtmServerEntry 5 }

gtmServerLimitMemAvailEnabled OBJECT-TYPE
	SYNTAX INTEGER {
		false(0),
		true(1)
	}
	MAX-ACCESS read-only
	STATUS current
	DESCRIPTION
		"The state indicating whether to set limit of available memory is
		enabled or not for the server."
	::= { gtmServerEntry 6 }

gtmServerLimitBitsPerSecEnabled OBJECT-TYPE
	SYNTAX INTEGER {
		false(0),
		true(1)
	}
	MAX-ACCESS read-only
	STATUS current
	DESCRIPTION
		"The state indicating whether to limit of number of bits per second
		is enabled or not for the server."
	::= { gtmServerEntry 7 }

gtmServerLimitPktsPerSecEnabled OBJECT-TYPE
	SYNTAX INTEGER {
		false(0),
		true(1)
	}
	MAX-ACCESS read-only
	STATUS current
	DESCRIPTION
		"The state indicating whether to set limit of number of packets
		per second is enabled or not for the server."
	::= { gtmServerEntry 8 }

gtmServerLimitConnEnabled OBJECT-TYPE
	SYNTAX INTEGER {
		false(0),
		true(1)
	}
	MAX-ACCESS read-only
	STATUS current
	DESCRIPTION
		"The state indicating whether to set limit of total connections
		is enabled or not for the server."
	::= { gtmServerEntry 9 }

gtmServerLimitConnPerSecEnabled OBJECT-TYPE
	SYNTAX INTEGER {
		false(0),
		true(1)
	}
	MAX-ACCESS read-only
	STATUS	 deprecated
	DESCRIPTION
		"Deprecated! This feature has been eliminated.
		The state indicating whether to set limit of connections per second
		is enabled or not for the server."
	::= { gtmServerEntry 10 }

gtmServerLimitCpuUsage OBJECT-TYPE
	SYNTAX Counter64
	MAX-ACCESS read-only
	STATUS current
	DESCRIPTION
		"The limit of CPU usage as a percentage for the server."
	::= { gtmServerEntry 11 }

gtmServerLimitMemAvail OBJECT-TYPE
	SYNTAX Counter64
	MAX-ACCESS read-only
	STATUS current
	DESCRIPTION
		"The limit of memory available in bytes for the server."
	::= { gtmServerEntry 12 }

gtmServerLimitBitsPerSec OBJECT-TYPE
	SYNTAX Counter64
	MAX-ACCESS read-only
	STATUS current
	DESCRIPTION
		"The limit of number of bits per second for the server."
	::= { gtmServerEntry 13 }

gtmServerLimitPktsPerSec OBJECT-TYPE
	SYNTAX Counter64
	MAX-ACCESS read-only
	STATUS current
	DESCRIPTION
		"The limit of number of packets per second for the server."
	::= { gtmServerEntry 14 }

gtmServerLimitConn OBJECT-TYPE
	SYNTAX Counter64
	MAX-ACCESS read-only
	STATUS current
	DESCRIPTION
		"The limit of total number of connections for the server."
	::= { gtmServerEntry 15 }

gtmServerLimitConnPerSec OBJECT-TYPE
	SYNTAX Counter64
	MAX-ACCESS read-only
	STATUS	 deprecated
	DESCRIPTION
		"Deprecated! This feature has been eliminated.
		The limit of number of connections per second for the server."
	::= { gtmServerEntry 16 }

gtmServerProberType OBJECT-TYPE
	SYNTAX InetAddressType
	MAX-ACCESS read-only
	STATUS	 deprecated
	DESCRIPTION
		"Deprecated! This is replaced by prober_pool.
		The prober address type of gtmServerProber."
	::= { gtmServerEntry 17 }

gtmServerProber OBJECT-TYPE
	SYNTAX InetAddress
	MAX-ACCESS read-only
	STATUS	 deprecated
	DESCRIPTION
		"Deprecated! This is replaced by prober_pool.
		The prober address for the specified server. It is interpreted within
		the context of an gtmServerProberType value."
	::= { gtmServerEntry 18 }

gtmServerMonitorRule OBJECT-TYPE
	SYNTAX LongDisplayString
	MAX-ACCESS read-only
	STATUS current
	DESCRIPTION
		"The name of monitor rule this server is used."
	::= { gtmServerEntry 19 }

gtmServerAllowSvcChk OBJECT-TYPE
	SYNTAX INTEGER {
		false(0),
		true(1)
	}
	MAX-ACCESS read-only
	STATUS current
	DESCRIPTION
		"The state indicating whether service check is allowed for
		the specified server."
	::= { gtmServerEntry 20 }

gtmServerAllowPath OBJECT-TYPE
	SYNTAX INTEGER {
		false(0),
		true(1)
	}
	MAX-ACCESS read-only
	STATUS current
	DESCRIPTION
		"The state indicating whether path information gathering is allowed
		for the specified server."
	::= { gtmServerEntry 21 }

gtmServerAllowSnmp OBJECT-TYPE
	SYNTAX INTEGER {
		false(0),
		true(1)
	}
	MAX-ACCESS read-only
	STATUS current
	DESCRIPTION
		"The state indicating whether SNMP information gathering is allowed
		for the specified server."
	::= { gtmServerEntry 22 }

gtmServerAutoconfState OBJECT-TYPE
	SYNTAX INTEGER {
		disabled(0),
		enabled(1),
		enablednoautodelete(2)
	}
	MAX-ACCESS read-only
	STATUS current
	DESCRIPTION
		"The state of auto configuration for BIGIP/3DNS servers.
	        for the specified server."
	::= { gtmServerEntry 23 }

gtmServerLinkAutoconfState OBJECT-TYPE
	SYNTAX INTEGER {
		disabled(0),
		enabled(1),
		enablednoautodelete(2)
	}
	MAX-ACCESS read-only
	STATUS current
	DESCRIPTION
		"The state of link auto configuration for BIGIP/3DNS servers.
	        for the specified server."
	::= { gtmServerEntry 24 }

--==================================================================
-- Gtm_server_stat
--==================================================================
gtmServerStatResetStats OBJECT-TYPE
	SYNTAX INTEGER
	MAX-ACCESS read-write
	STATUS	 deprecated
	DESCRIPTION
		"Deprecated!.
		The action to reset resettable statistics data in gtmServerStat.
		 Setting this value to 1 will reset statistics data.
		 Note, some statistics data may not be reset including data that are incremental counters."
	::= { gtmServerStat 1 }

gtmServerStatNumber OBJECT-TYPE
	SYNTAX INTEGER
	MAX-ACCESS read-only
	STATUS	 deprecated
	DESCRIPTION
		"Deprecated!.
		The number of gtmServerStat entries in the table."
	::= { gtmServerStat 2 }

gtmServerStatTable OBJECT-TYPE
	SYNTAX SEQUENCE OF GtmServerStatEntry
	MAX-ACCESS not-accessible
	STATUS deprecated
	DESCRIPTION
		"Deprecated! Replaced by gtmServerStat2 table.
		A table containing statistics information of servers within associated
		 data center for GTM (Global Traffic Management)."
	::= { gtmServerStat 3 }

gtmServerStatEntry OBJECT-TYPE
	SYNTAX  GtmServerStatEntry
	MAX-ACCESS not-accessible
	STATUS deprecated
	DESCRIPTION
		"Columns in the gtmServerStat Table"
	INDEX {
		gtmServerStatName
	}
	::= { gtmServerStatTable 1 }

GtmServerStatEntry ::=
	SEQUENCE {
        	gtmServerStatName                                         LongDisplayString,
        	gtmServerStatUnitId                                       INTEGER,
        	gtmServerStatVsPicks                                      Counter64,
        	gtmServerStatCpuUsage                                     Counter64,
        	gtmServerStatMemAvail                                     Counter64,
        	gtmServerStatBitsPerSecIn                                 Counter64,
        	gtmServerStatBitsPerSecOut                                Counter64,
        	gtmServerStatPktsPerSecIn                                 Counter64,
        	gtmServerStatPktsPerSecOut                                Counter64,
        	gtmServerStatConnections                                  Counter64,
        	gtmServerStatConnRate                                     Counter64
	}

gtmServerStatName OBJECT-TYPE
	SYNTAX LongDisplayString
	MAX-ACCESS read-only
	STATUS	 deprecated
	DESCRIPTION
		"Deprecated! Replaced by data in gtmServerStat2 table.
		The name of a server."
	::= { gtmServerStatEntry 1 }

gtmServerStatUnitId OBJECT-TYPE
	SYNTAX INTEGER
	MAX-ACCESS read-only
	STATUS	 deprecated
	DESCRIPTION
		"Deprecated! Replaced by data in gtmServerStat2 table.
		The unit ID of the specified server."
	::= { gtmServerStatEntry 2 }

gtmServerStatVsPicks OBJECT-TYPE
	SYNTAX Counter64
	MAX-ACCESS read-only
	STATUS	 deprecated
	DESCRIPTION
		"Deprecated! Replaced by data in gtmServerStat2 table.
		How many times a virtual server of the specified server was picked
		during resolution of a domain name. I.E amazon.com got resolved to
		a particular virtual address X times."
	::= { gtmServerStatEntry 3 }

gtmServerStatCpuUsage OBJECT-TYPE
	SYNTAX Counter64
	MAX-ACCESS read-only
	STATUS	 deprecated
	DESCRIPTION
		"Deprecated! Replaced by data in gtmServerStat2 table.
		The CPU usage in percentage for the specified server."
	::= { gtmServerStatEntry 4 }

gtmServerStatMemAvail OBJECT-TYPE
	SYNTAX Counter64
	MAX-ACCESS read-only
	STATUS	 deprecated
	DESCRIPTION
		"Deprecated! Replaced by data in gtmServerStat2 table.
		The memory available in bytes for the specified server."
	::= { gtmServerStatEntry 5 }

gtmServerStatBitsPerSecIn OBJECT-TYPE
	SYNTAX Counter64
	MAX-ACCESS read-only
	STATUS	 deprecated
	DESCRIPTION
		"Deprecated! Replaced by data in gtmServerStat2 table.
		The number of bits per second received by the specified server."
	::= { gtmServerStatEntry 6 }

gtmServerStatBitsPerSecOut OBJECT-TYPE
	SYNTAX Counter64
	MAX-ACCESS read-only
	STATUS	 deprecated
	DESCRIPTION
		"Deprecated! Replaced by data in gtmServerStat2 table.
		The number of bits per second sent from the specified server."
	::= { gtmServerStatEntry 7 }

gtmServerStatPktsPerSecIn OBJECT-TYPE
	SYNTAX Counter64
	MAX-ACCESS read-only
	STATUS	 deprecated
	DESCRIPTION
		"Deprecated! Replaced by data in gtmServerStat2 table.
		The number of packets per second received by the specified server."
	::= { gtmServerStatEntry 8 }

gtmServerStatPktsPerSecOut OBJECT-TYPE
	SYNTAX Counter64
	MAX-ACCESS read-only
	STATUS	 deprecated
	DESCRIPTION
		"Deprecated! Replaced by data in gtmServerStat2 table.
		The number of packets per second sent from the specified server."
	::= { gtmServerStatEntry 9 }

gtmServerStatConnections OBJECT-TYPE
	SYNTAX Counter64
	MAX-ACCESS read-only
	STATUS	 deprecated
	DESCRIPTION
		"Deprecated! Replaced by data in gtmServerStat2 table.
		The number of total connections to the specified server."
	::= { gtmServerStatEntry 10 }

gtmServerStatConnRate OBJECT-TYPE
	SYNTAX Counter64
	MAX-ACCESS read-only
	STATUS	 deprecated
	DESCRIPTION
		"Deprecated! Replaced by data in gtmServerStat2 table.
		The connection rate (current connection rate/connection rate limit)
		in percentage for the specified server."
	::= { gtmServerStatEntry 11 }

--==================================================================
-- Gtm_server_status
--==================================================================
gtmServerStatusNumber OBJECT-TYPE
	SYNTAX INTEGER
	MAX-ACCESS read-only
	STATUS current
	DESCRIPTION
		"The number of gtmServerStatus entries in the table."
	::= { gtmServerStatus 1 }

gtmServerStatusTable OBJECT-TYPE
	SYNTAX SEQUENCE OF GtmServerStatusEntry
	MAX-ACCESS not-accessible
	STATUS current
	DESCRIPTION
		"A table containing status information of servers within associated
		 data center for GTM (Global Traffic Management)."
	::= { gtmServerStatus 2 }

gtmServerStatusEntry OBJECT-TYPE
	SYNTAX  GtmServerStatusEntry
	MAX-ACCESS not-accessible
	STATUS current
	DESCRIPTION
		"Columns in the gtmServerStatus Table"
	INDEX {
		gtmServerStatusName
	}
	::= { gtmServerStatusTable 1 }

GtmServerStatusEntry ::=
	SEQUENCE {
        	gtmServerStatusName                                       LongDisplayString,
        	gtmServerStatusAvailState                                 INTEGER,
        	gtmServerStatusEnabledState                               INTEGER,
        	gtmServerStatusParentType                                 Gauge,
        	gtmServerStatusDetailReason                               LongDisplayString
	}

gtmServerStatusName OBJECT-TYPE
	SYNTAX LongDisplayString
	MAX-ACCESS read-only
	STATUS current
	DESCRIPTION
		"The name of a server."
	::= { gtmServerStatusEntry 1 }

gtmServerStatusAvailState OBJECT-TYPE
	SYNTAX INTEGER {
		none(0),
		green(1),
		yellow(2),
		red(3),
		blue(4),
		gray(5)
	}
	MAX-ACCESS read-only
	STATUS current
	DESCRIPTION
		"The availability of the specified server indicated by color.
		none - error;
		green - available in some capacity;
		yellow - not currently available;
		red - not available;
		blue - availability is unknown;
		gray - unlicensed."
	::= { gtmServerStatusEntry 2 }

gtmServerStatusEnabledState OBJECT-TYPE
	SYNTAX INTEGER {
		none(0),
		enabled(1),
		disabled(2),
		disabledbyparent(3)
	}
	MAX-ACCESS read-only
	STATUS current
	DESCRIPTION
		"The activity status of the specified server, as specified
		by the user."
	::= { gtmServerStatusEntry 3 }

gtmServerStatusParentType OBJECT-TYPE
	SYNTAX Gauge
	MAX-ACCESS read-only
	STATUS	 deprecated
	DESCRIPTION
		"Deprecated! This is an internal data.
		The type of parent object which disabled the specified server."
	::= { gtmServerStatusEntry 4 }

gtmServerStatusDetailReason OBJECT-TYPE
	SYNTAX LongDisplayString
	MAX-ACCESS read-only
	STATUS current
	DESCRIPTION
		"The detail description of the specified node's status."
	::= { gtmServerStatusEntry 5 }

--==================================================================
-- Gtm_top_item
--==================================================================
gtmTopItemNumber OBJECT-TYPE
	SYNTAX INTEGER
	MAX-ACCESS read-only
	STATUS current
	DESCRIPTION
		"The number of gtmTopItem entries in the table."
	::= { gtmTopItem 1 }

gtmTopItemTable OBJECT-TYPE
	SYNTAX SEQUENCE OF GtmTopItemEntry
	MAX-ACCESS not-accessible
	STATUS current
	DESCRIPTION
		"A table containing information of topology attributes for GTM (Global Traffic Management)."
	::= { gtmTopItem 2 }

gtmTopItemEntry OBJECT-TYPE
	SYNTAX  GtmTopItemEntry
	MAX-ACCESS not-accessible
	STATUS current
	DESCRIPTION
		"Columns in the gtmTopItem Table"
	INDEX {
		gtmTopItemLdnsType,
		gtmTopItemLdnsNegate,
		gtmTopItemLdnsEntry,
		gtmTopItemServerType,
		gtmTopItemServerNegate,
		gtmTopItemServerEntry
	}
	::= { gtmTopItemTable 1 }

GtmTopItemEntry ::=
	SEQUENCE {
        	gtmTopItemLdnsType                                        INTEGER,
        	gtmTopItemLdnsNegate                                      INTEGER,
        	gtmTopItemLdnsEntry                                       LongDisplayString,
        	gtmTopItemServerType                                      INTEGER,
        	gtmTopItemServerNegate                                    INTEGER,
        	gtmTopItemServerEntry                                     LongDisplayString,
        	gtmTopItemWeight                                          Gauge,
        	gtmTopItemOrder                                           Gauge
	}

gtmTopItemLdnsType OBJECT-TYPE
	SYNTAX INTEGER {
		cidr(0),
		region(1),
		continent(2),
		country(3),
		state(4),
		pool(5),
		datacenter(6),
		ispregion(7),
		geoipIsp(8)
	}
	MAX-ACCESS read-only
	STATUS current
	DESCRIPTION
		"The type of topology end point for the LDNS."
	::= { gtmTopItemEntry 1 }

gtmTopItemLdnsNegate OBJECT-TYPE
	SYNTAX INTEGER {
		false(0),
		true(1)
	}
	MAX-ACCESS read-only
	STATUS current
	DESCRIPTION
		"The state indicating whether the end point is not equal to
		the definition the LDNS."
	::= { gtmTopItemEntry 2 }

gtmTopItemLdnsEntry OBJECT-TYPE
	SYNTAX LongDisplayString
	MAX-ACCESS read-only
	STATUS current
	DESCRIPTION
		"The LDNS entry which could be an IP address, a region name,
		a continent, etc."
	::= { gtmTopItemEntry 3 }

gtmTopItemServerType OBJECT-TYPE
	SYNTAX INTEGER {
		cidr(0),
		region(1),
		continent(2),
		country(3),
		state(4),
		pool(5),
		datacenter(6),
		ispregion(7),
		geoipIsp(8)
	}
	MAX-ACCESS read-only
	STATUS current
	DESCRIPTION
		"The type of topology end point for the virtual server."
	::= { gtmTopItemEntry 4 }

gtmTopItemServerNegate OBJECT-TYPE
	SYNTAX INTEGER {
		false(0),
		true(1)
	}
	MAX-ACCESS read-only
	STATUS current
	DESCRIPTION
		"The state indicating whether the end point is not equal to
		the definition for the virtual server."
	::= { gtmTopItemEntry 5 }

gtmTopItemServerEntry OBJECT-TYPE
	SYNTAX LongDisplayString
	MAX-ACCESS read-only
	STATUS current
	DESCRIPTION
		"The server entry which could be an IP address, a region name,
		a continent, etc."
	::= { gtmTopItemEntry 6 }

gtmTopItemWeight OBJECT-TYPE
	SYNTAX Gauge
	MAX-ACCESS read-only
	STATUS current
	DESCRIPTION
		"The relative weight for the topology record."
	::= { gtmTopItemEntry 7 }

gtmTopItemOrder OBJECT-TYPE
	SYNTAX Gauge
	MAX-ACCESS read-only
	STATUS current
	DESCRIPTION
		"The order of the record without longest match sorting."
	::= { gtmTopItemEntry 8 }

--==================================================================
-- Gtm_vs
--==================================================================
gtmVsNumber OBJECT-TYPE
	SYNTAX INTEGER
	MAX-ACCESS read-only
	STATUS current
	DESCRIPTION
		"The number of gtmVirtualServ entries in the table."
	::= { gtmVirtualServ 1 }

gtmVsTable OBJECT-TYPE
	SYNTAX SEQUENCE OF GtmVsEntry
	MAX-ACCESS not-accessible
	STATUS current
	DESCRIPTION
		"A table containing information of virtual servers for GTM (Global Traffic Management)."
	::= { gtmVirtualServ 2 }

gtmVsEntry OBJECT-TYPE
	SYNTAX  GtmVsEntry
	MAX-ACCESS not-accessible
	STATUS current
	DESCRIPTION
		"Columns in the gtmVs Table"
	INDEX {
		gtmVsServerName,
		gtmVsName
	}
	::= { gtmVsTable 1 }

GtmVsEntry ::=
	SEQUENCE {
        	gtmVsIpType                                               InetAddressType,
        	gtmVsIp                                                   InetAddress,
        	gtmVsPort                                                 InetPortNumber,
        	gtmVsName                                                 LongDisplayString,
        	gtmVsServerName                                           LongDisplayString,
        	gtmVsIpXlatedType                                         InetAddressType,
        	gtmVsIpXlated                                             InetAddress,
        	gtmVsPortXlated                                           InetPortNumber,
        	gtmVsLimitCpuUsageEnabled                                 INTEGER,
        	gtmVsLimitMemAvailEnabled                                 INTEGER,
        	gtmVsLimitBitsPerSecEnabled                               INTEGER,
        	gtmVsLimitPktsPerSecEnabled                               INTEGER,
        	gtmVsLimitConnEnabled                                     INTEGER,
        	gtmVsLimitConnPerSecEnabled                               INTEGER,
        	gtmVsLimitCpuUsage                                        Counter64,
        	gtmVsLimitMemAvail                                        Counter64,
        	gtmVsLimitBitsPerSec                                      Counter64,
        	gtmVsLimitPktsPerSec                                      Counter64,
        	gtmVsLimitConn                                            Counter64,
        	gtmVsLimitConnPerSec                                      Counter64,
        	gtmVsMonitorRule                                          LongDisplayString,
        	gtmVsEnabled                                              INTEGER,
        	gtmVsLinkName                                             LongDisplayString,
        	gtmVsLtmName                                              LongDisplayString
	}

gtmVsIpType OBJECT-TYPE
	SYNTAX InetAddressType
	MAX-ACCESS read-only
	STATUS current
	DESCRIPTION
		"The IP address type of gtmVirtualServIp."
	::= { gtmVsEntry 1 }

gtmVsIp OBJECT-TYPE
	SYNTAX InetAddress
	MAX-ACCESS read-only
	STATUS current
	DESCRIPTION
		"The IP address of a virtual server. It is interpreted
	        within the context of a gtmVirtualServIpType value."
	::= { gtmVsEntry 2 }

gtmVsPort OBJECT-TYPE
	SYNTAX InetPortNumber
	MAX-ACCESS read-only
	STATUS current
	DESCRIPTION
		"The port of a virtual server."
	::= { gtmVsEntry 3 }

gtmVsName OBJECT-TYPE
	SYNTAX LongDisplayString
	MAX-ACCESS read-only
	STATUS current
	DESCRIPTION
		"The name of the specified virtual server."
	::= { gtmVsEntry 4 }

gtmVsServerName OBJECT-TYPE
	SYNTAX LongDisplayString
	MAX-ACCESS read-only
	STATUS current
	DESCRIPTION
		"The name of the server with which the specified virtual server associates."
	::= { gtmVsEntry 5 }

gtmVsIpXlatedType OBJECT-TYPE
	SYNTAX InetAddressType
	MAX-ACCESS read-only
	STATUS current
	DESCRIPTION
		"The IP address type of gtmVirtualServIpXlated."
	::= { gtmVsEntry 6 }

gtmVsIpXlated OBJECT-TYPE
	SYNTAX InetAddress
	MAX-ACCESS read-only
	STATUS current
	DESCRIPTION
		"The translated IP address for the specified virtual server.
		It is interpreted within the context of a gtmVirtualServIpXlatedType value."
	::= { gtmVsEntry 7 }

gtmVsPortXlated OBJECT-TYPE
	SYNTAX InetPortNumber
	MAX-ACCESS read-only
	STATUS current
	DESCRIPTION
		"The translated port for the specified virtual server."
	::= { gtmVsEntry 8 }

gtmVsLimitCpuUsageEnabled OBJECT-TYPE
	SYNTAX INTEGER {
		false(0),
		true(1)
	}
	MAX-ACCESS read-only
	STATUS current
	DESCRIPTION
		"The state indicating whether to set limit of CPU usage is enabled
		or not for the virtual server."
	::= { gtmVsEntry 9 }

gtmVsLimitMemAvailEnabled OBJECT-TYPE
	SYNTAX INTEGER {
		false(0),
		true(1)
	}
	MAX-ACCESS read-only
	STATUS current
	DESCRIPTION
		"The state indicating whether to set limit of available memory is
		enabled or not for the virtual server."
	::= { gtmVsEntry 10 }

gtmVsLimitBitsPerSecEnabled OBJECT-TYPE
	SYNTAX INTEGER {
		false(0),
		true(1)
	}
	MAX-ACCESS read-only
	STATUS current
	DESCRIPTION
		"The state indicating whether to limit of number of bits per second
		is enabled or not for the virtual server."
	::= { gtmVsEntry 11 }

gtmVsLimitPktsPerSecEnabled OBJECT-TYPE
	SYNTAX INTEGER {
		false(0),
		true(1)
	}
	MAX-ACCESS read-only
	STATUS current
	DESCRIPTION
		"The state indicating whether to set limit of number of packets
		per second is enabled or not for the virtual server."
	::= { gtmVsEntry 12 }

gtmVsLimitConnEnabled OBJECT-TYPE
	SYNTAX INTEGER {
		false(0),
		true(1)
	}
	MAX-ACCESS read-only
	STATUS current
	DESCRIPTION
		"The state indicating whether to set limit of total connections
		is enabled or not for the virtual server."
	::= { gtmVsEntry 13 }

gtmVsLimitConnPerSecEnabled OBJECT-TYPE
	SYNTAX INTEGER {
		false(0),
		true(1)
	}
	MAX-ACCESS read-only
	STATUS	 deprecated
	DESCRIPTION
		"Deprecated! This feature has been eliminated.
		The state indicating whether to set limit of connections per second
		is enabled or not for the virtual server."
	::= { gtmVsEntry 14 }

gtmVsLimitCpuUsage OBJECT-TYPE
	SYNTAX Counter64
	MAX-ACCESS read-only
	STATUS current
	DESCRIPTION
		"The limit of CPU usage as a percentage for the virtual server."
	::= { gtmVsEntry 15 }

gtmVsLimitMemAvail OBJECT-TYPE
	SYNTAX Counter64
	MAX-ACCESS read-only
	STATUS current
	DESCRIPTION
		"The limit of memory available in bytes for the virtual server."
	::= { gtmVsEntry 16 }

gtmVsLimitBitsPerSec OBJECT-TYPE
	SYNTAX Counter64
	MAX-ACCESS read-only
	STATUS current
	DESCRIPTION
		"The limit of number of bits per second for the virtual server."
	::= { gtmVsEntry 17 }

gtmVsLimitPktsPerSec OBJECT-TYPE
	SYNTAX Counter64
	MAX-ACCESS read-only
	STATUS current
	DESCRIPTION
		"The limit of number of packets per second for the virtual server."
	::= { gtmVsEntry 18 }

gtmVsLimitConn OBJECT-TYPE
	SYNTAX Counter64
	MAX-ACCESS read-only
	STATUS current
	DESCRIPTION
		"The limit of total number of connections for the virtual server."
	::= { gtmVsEntry 19 }

gtmVsLimitConnPerSec OBJECT-TYPE
	SYNTAX Counter64
	MAX-ACCESS read-only
	STATUS	 deprecated
	DESCRIPTION
		"Deprecated! This feature has been eliminated.
		The limit of number of connections per second for the virtual server."
	::= { gtmVsEntry 20 }

gtmVsMonitorRule OBJECT-TYPE
	SYNTAX LongDisplayString
	MAX-ACCESS read-only
	STATUS current
	DESCRIPTION
		"The name of the monitor rule for this virtual server."
	::= { gtmVsEntry 21 }

gtmVsEnabled OBJECT-TYPE
	SYNTAX INTEGER {
		disable(0),
		enable(1)
	}
	MAX-ACCESS read-only
	STATUS current
	DESCRIPTION
		"The state indicating whether the virtual server is enabled or not."
	::= { gtmVsEntry 22 }

gtmVsLinkName OBJECT-TYPE
	SYNTAX LongDisplayString
	MAX-ACCESS read-only
	STATUS current
	DESCRIPTION
		"The parent link of this virtual server."
	::= { gtmVsEntry 23 }

gtmVsLtmName OBJECT-TYPE
	SYNTAX LongDisplayString
	MAX-ACCESS read-only
	STATUS current
	DESCRIPTION
		"The user configured LTM name of the specified virtual server.
	        This string is not populated as a result of monitoring activity."
	::= { gtmVsEntry 24 }

--==================================================================
-- Gtm_vs_depends
--==================================================================
gtmVsDepsNumber OBJECT-TYPE
	SYNTAX INTEGER
	MAX-ACCESS read-only
	STATUS current
	DESCRIPTION
		"The number of gtmVirtualServDepends entries in the table."
	::= { gtmVirtualServDepends 1 }

gtmVsDepsTable OBJECT-TYPE
	SYNTAX SEQUENCE OF GtmVsDepsEntry
	MAX-ACCESS not-accessible
	STATUS current
	DESCRIPTION
		"A table containing information of virtual servers' dependencies on other virtual servers for GTM (Global Traffic Management)."
	::= { gtmVirtualServDepends 2 }

gtmVsDepsEntry OBJECT-TYPE
	SYNTAX  GtmVsDepsEntry
	MAX-ACCESS not-accessible
	STATUS current
	DESCRIPTION
		"Columns in the gtmVsDeps Table"
	INDEX {
		gtmVsDepsServerName,
		gtmVsDepsVsName,
		gtmVsDepsDependServerName,
		gtmVsDepsDependVsName
	}
	::= { gtmVsDepsTable 1 }

GtmVsDepsEntry ::=
	SEQUENCE {
        	gtmVsDepsIpType                                           InetAddressType,
        	gtmVsDepsIp                                               InetAddress,
        	gtmVsDepsPort                                             InetPortNumber,
        	gtmVsDepsVipType                                          InetAddressType,
        	gtmVsDepsVip                                              InetAddress,
        	gtmVsDepsVport                                            InetPortNumber,
        	gtmVsDepsServerName                                       LongDisplayString,
        	gtmVsDepsVsName                                           LongDisplayString,
        	gtmVsDepsDependServerName                                 LongDisplayString,
        	gtmVsDepsDependVsName                                     LongDisplayString
	}

gtmVsDepsIpType OBJECT-TYPE
	SYNTAX InetAddressType
	MAX-ACCESS read-only
	STATUS	 deprecated
	DESCRIPTION
		"Deprecated! use server_name and vs_name instead,
		The IP address type of gtmVsDepsIp."
	::= { gtmVsDepsEntry 1 }

gtmVsDepsIp OBJECT-TYPE
	SYNTAX InetAddress
	MAX-ACCESS read-only
	STATUS	 deprecated
	DESCRIPTION
		"Deprecated! use server_name and vs_name instead,
		The IP address of a virtual server. It is interpreted within
	        the context of gtmVsDepsIpType value."
	::= { gtmVsDepsEntry 2 }

gtmVsDepsPort OBJECT-TYPE
	SYNTAX InetPortNumber
	MAX-ACCESS read-only
	STATUS	 deprecated
	DESCRIPTION
		"Deprecated! use server_name and vs_name instead,
	 	The port of a virtual server."
	::= { gtmVsDepsEntry 3 }

gtmVsDepsVipType OBJECT-TYPE
	SYNTAX InetAddressType
	MAX-ACCESS read-only
	STATUS	 deprecated
	DESCRIPTION
		"Deprecated! use depend server_name and vs_name instead,
		The IP address type of gtmVsDepsVip"
	::= { gtmVsDepsEntry 4 }

gtmVsDepsVip OBJECT-TYPE
	SYNTAX InetAddress
	MAX-ACCESS read-only
	STATUS	 deprecated
	DESCRIPTION
		"Deprecated! use depend server_name and vs_name instead,
		The IP address of a virtual server on which the specified virtual server depends.
		It is interpreted within the context of gtmVsDepsOnVipType value."
	::= { gtmVsDepsEntry 5 }

gtmVsDepsVport OBJECT-TYPE
	SYNTAX InetPortNumber
	MAX-ACCESS read-only
	STATUS	 deprecated
	DESCRIPTION
		"Deprecated! depend use server_name and vs_name instead,
	 	The port of a virtual server on  which the specified virtual server depends."
	::= { gtmVsDepsEntry 6 }

gtmVsDepsServerName OBJECT-TYPE
	SYNTAX LongDisplayString
	MAX-ACCESS read-only
	STATUS current
	DESCRIPTION
		"The name of the server with which the specified virtual server is associated."
	::= { gtmVsDepsEntry 7 }

gtmVsDepsVsName OBJECT-TYPE
	SYNTAX LongDisplayString
	MAX-ACCESS read-only
	STATUS current
	DESCRIPTION
		"The virtual server name."
	::= { gtmVsDepsEntry 8 }

gtmVsDepsDependServerName OBJECT-TYPE
	SYNTAX LongDisplayString
	MAX-ACCESS read-only
	STATUS current
	DESCRIPTION
		"The server name of a virtual server on which the specified virtual server depends."
	::= { gtmVsDepsEntry 9 }

gtmVsDepsDependVsName OBJECT-TYPE
	SYNTAX LongDisplayString
	MAX-ACCESS read-only
	STATUS current
	DESCRIPTION
		"The virtual server name on which the specified virtual server depends."
	::= { gtmVsDepsEntry 10 }

--==================================================================
-- Gtm_vs_stat
--==================================================================
gtmVsStatResetStats OBJECT-TYPE
	SYNTAX INTEGER
	MAX-ACCESS read-write
	STATUS current
	DESCRIPTION
		"The action to reset resettable statistics data in gtmVirtualServStat.
		 Setting this value to 1 will reset statistics data.
		 Note, some statistics data may not be reset including data that are incremental counters."
	::= { gtmVirtualServStat 1 }

gtmVsStatNumber OBJECT-TYPE
	SYNTAX INTEGER
	MAX-ACCESS read-only
	STATUS current
	DESCRIPTION
		"The number of gtmVirtualServStat entries in the table."
	::= { gtmVirtualServStat 2 }

gtmVsStatTable OBJECT-TYPE
	SYNTAX SEQUENCE OF GtmVsStatEntry
	MAX-ACCESS not-accessible
	STATUS current
	DESCRIPTION
		"A table containing statistics information of virtual servers
		for GTM (Global Traffic Management)."
	::= { gtmVirtualServStat 3 }

gtmVsStatEntry OBJECT-TYPE
	SYNTAX  GtmVsStatEntry
	MAX-ACCESS not-accessible
	STATUS current
	DESCRIPTION
		"Columns in the gtmVsStat Table"
	INDEX {
		gtmVsStatServerName,
		gtmVsStatName
	}
	::= { gtmVsStatTable 1 }

GtmVsStatEntry ::=
	SEQUENCE {
        	gtmVsStatIpType                                           InetAddressType,
        	gtmVsStatIp                                               InetAddress,
        	gtmVsStatPort                                             InetPortNumber,
        	gtmVsStatName                                             LongDisplayString,
        	gtmVsStatCpuUsage                                         Counter64,
        	gtmVsStatMemAvail                                         Counter64,
        	gtmVsStatBitsPerSecIn                                     Counter64,
        	gtmVsStatBitsPerSecOut                                    Counter64,
        	gtmVsStatPktsPerSecIn                                     Counter64,
        	gtmVsStatPktsPerSecOut                                    Counter64,
        	gtmVsStatConnections                                      Counter64,
        	gtmVsStatConnRate                                         Counter64,
        	gtmVsStatVsScore                                          Counter64,
        	gtmVsStatServerName                                       LongDisplayString
	}

gtmVsStatIpType OBJECT-TYPE
	SYNTAX InetAddressType
	MAX-ACCESS read-only
	STATUS	 deprecated
	DESCRIPTION
		"Deprecated! use server_name and vs_name instead,
		The IP address type of gtmVirtualServStatIp."
	::= { gtmVsStatEntry 1 }

gtmVsStatIp OBJECT-TYPE
	SYNTAX InetAddress
	MAX-ACCESS read-only
	STATUS	 deprecated
	DESCRIPTION
		"Deprecated! use server_name and vs_name instead,
		The IP address of a virtual server. It is interpreted within
	        the context of gtmVirtualServStatIpType value."
	::= { gtmVsStatEntry 2 }

gtmVsStatPort OBJECT-TYPE
	SYNTAX InetPortNumber
	MAX-ACCESS read-only
	STATUS	 deprecated
	DESCRIPTION
		"Deprecated! use server_name and vs_name instead,
	 	The port of a virtual server."
	::= { gtmVsStatEntry 3 }

gtmVsStatName OBJECT-TYPE
	SYNTAX LongDisplayString
	MAX-ACCESS read-only
	STATUS current
	DESCRIPTION
		"The name of the specified virtual server."
	::= { gtmVsStatEntry 4 }

gtmVsStatCpuUsage OBJECT-TYPE
	SYNTAX Counter64
	MAX-ACCESS read-only
	STATUS current
	DESCRIPTION
		"The CPU usage in percentage for the specified virtual server."
	::= { gtmVsStatEntry 5 }

gtmVsStatMemAvail OBJECT-TYPE
	SYNTAX Counter64
	MAX-ACCESS read-only
	STATUS current
	DESCRIPTION
		"The memory available in bytes for the specified virtual server."
	::= { gtmVsStatEntry 6 }

gtmVsStatBitsPerSecIn OBJECT-TYPE
	SYNTAX Counter64
	MAX-ACCESS read-only
	STATUS current
	DESCRIPTION
		"The number of bits per second received by the specified virtual server."
	::= { gtmVsStatEntry 7 }

gtmVsStatBitsPerSecOut OBJECT-TYPE
	SYNTAX Counter64
	MAX-ACCESS read-only
	STATUS current
	DESCRIPTION
		"The number of bits per second sent from the specified virtual server."
	::= { gtmVsStatEntry 8 }

gtmVsStatPktsPerSecIn OBJECT-TYPE
	SYNTAX Counter64
	MAX-ACCESS read-only
	STATUS current
	DESCRIPTION
		"The number of packets per second received by the specified virtual server."
	::= { gtmVsStatEntry 9 }

gtmVsStatPktsPerSecOut OBJECT-TYPE
	SYNTAX Counter64
	MAX-ACCESS read-only
	STATUS current
	DESCRIPTION
		"The number of packets per second sent from the specified virtual server."
	::= { gtmVsStatEntry 10 }

gtmVsStatConnections OBJECT-TYPE
	SYNTAX Counter64
	MAX-ACCESS read-only
	STATUS current
	DESCRIPTION
		"The number of total connections to the specified virtual server."
	::= { gtmVsStatEntry 11 }

gtmVsStatConnRate OBJECT-TYPE
	SYNTAX Counter64
	MAX-ACCESS read-only
	STATUS	 deprecated
	DESCRIPTION
		"Deprecated!
		Replaced by gtmVsStatVsScore.
		The connection rate (current connection rate/connection rate limit)
		in percentage for the specified virtual server."
	::= { gtmVsStatEntry 12 }

gtmVsStatVsScore OBJECT-TYPE
	SYNTAX Counter64
	MAX-ACCESS read-only
	STATUS current
	DESCRIPTION
		"A user-defined value that specifies the ranking of the virtual server
		when compared to other virtual servers within the same pool."
	::= { gtmVsStatEntry 13 }

gtmVsStatServerName OBJECT-TYPE
	SYNTAX LongDisplayString
	MAX-ACCESS read-only
	STATUS current
	DESCRIPTION
		"The name of the server with which the specified virtual server is associated."
	::= { gtmVsStatEntry 14 }

--==================================================================
-- Gtm_vs_status
--==================================================================
gtmVsStatusNumber OBJECT-TYPE
	SYNTAX INTEGER
	MAX-ACCESS read-only
	STATUS current
	DESCRIPTION
		"The number of gtmVirtualServStatus entries in the table."
	::= { gtmVirtualServStatus 1 }

gtmVsStatusTable OBJECT-TYPE
	SYNTAX SEQUENCE OF GtmVsStatusEntry
	MAX-ACCESS not-accessible
	STATUS current
	DESCRIPTION
		"A table containing status information of virtual servers
		for GTM (Global Traffic Management)."
	::= { gtmVirtualServStatus 2 }

gtmVsStatusEntry OBJECT-TYPE
	SYNTAX  GtmVsStatusEntry
	MAX-ACCESS not-accessible
	STATUS current
	DESCRIPTION
		"Columns in the gtmVsStatus Table"
	INDEX {
		gtmVsStatusServerName,
		gtmVsStatusVsName
	}
	::= { gtmVsStatusTable 1 }

GtmVsStatusEntry ::=
	SEQUENCE {
        	gtmVsStatusIpType                                         InetAddressType,
        	gtmVsStatusIp                                             InetAddress,
        	gtmVsStatusPort                                           InetPortNumber,
        	gtmVsStatusAvailState                                     INTEGER,
        	gtmVsStatusEnabledState                                   INTEGER,
        	gtmVsStatusParentType                                     Gauge,
        	gtmVsStatusDetailReason                                   LongDisplayString,
        	gtmVsStatusVsName                                         LongDisplayString,
        	gtmVsStatusServerName                                     LongDisplayString
	}

gtmVsStatusIpType OBJECT-TYPE
	SYNTAX InetAddressType
	MAX-ACCESS read-only
	STATUS	 deprecated
	DESCRIPTION
		"Deprecated! use server_name and vs_name instead,
		The IP address type of gtmVirtualServStatusIp."
	::= { gtmVsStatusEntry 1 }

gtmVsStatusIp OBJECT-TYPE
	SYNTAX InetAddress
	MAX-ACCESS read-only
	STATUS	 deprecated
	DESCRIPTION
		"Deprecated! use server_name and vs_name instead,
		The IP address of a virtual server. It is interpreted within
	        the context of gtmVirtualServStatusIpType value."
	::= { gtmVsStatusEntry 2 }

gtmVsStatusPort OBJECT-TYPE
	SYNTAX InetPortNumber
	MAX-ACCESS read-only
	STATUS	 deprecated
	DESCRIPTION
		"Deprecated! use server_name and vs_name instead,
	 	The port of a virtual server."
	::= { gtmVsStatusEntry 3 }

gtmVsStatusAvailState OBJECT-TYPE
	SYNTAX INTEGER {
		none(0),
		green(1),
		yellow(2),
		red(3),
		blue(4),
		gray(5)
	}
	MAX-ACCESS read-only
	STATUS current
	DESCRIPTION
		"The availability of the specified virtual server indicated by color.
		none - error;
		green - available in some capacity;
		yellow - not currently available;
		red - not available;
		blue - availability is unknown;
		gray - unlicensed."
	::= { gtmVsStatusEntry 4 }

gtmVsStatusEnabledState OBJECT-TYPE
	SYNTAX INTEGER {
		none(0),
		enabled(1),
		disabled(2),
		disabledbyparent(3)
	}
	MAX-ACCESS read-only
	STATUS current
	DESCRIPTION
		"The activity status of the specified virtual server, as specified
		by the user."
	::= { gtmVsStatusEntry 5 }

gtmVsStatusParentType OBJECT-TYPE
	SYNTAX Gauge
	MAX-ACCESS read-only
	STATUS	 deprecated
	DESCRIPTION
		"Deprecated! This is an internal data.
		The type of parent object which disabled this virtual server."
	::= { gtmVsStatusEntry 6 }

gtmVsStatusDetailReason OBJECT-TYPE
	SYNTAX LongDisplayString
	MAX-ACCESS read-only
	STATUS current
	DESCRIPTION
		"The detail description of the specified virtual server's status."
	::= { gtmVsStatusEntry 7 }

gtmVsStatusVsName OBJECT-TYPE
	SYNTAX LongDisplayString
	MAX-ACCESS read-only
	STATUS current
	DESCRIPTION
		"The name of the specified virtual server."
	::= { gtmVsStatusEntry 8 }

gtmVsStatusServerName OBJECT-TYPE
	SYNTAX LongDisplayString
	MAX-ACCESS read-only
	STATUS current
	DESCRIPTION
		"The name of the server with which the specified virtual server is associated."
	::= { gtmVsStatusEntry 9 }

--==================================================================
-- Gtm_wideip
--==================================================================
gtmWideipNumber OBJECT-TYPE
	SYNTAX INTEGER
	MAX-ACCESS read-only
	STATUS current
	DESCRIPTION
		"The number of gtmWideip entries in the table."
	::= { gtmWideip 1 }

gtmWideipTable OBJECT-TYPE
	SYNTAX SEQUENCE OF GtmWideipEntry
	MAX-ACCESS not-accessible
	STATUS current
	DESCRIPTION
		"A table containing information of wide IPs for GTM (Global Traffic Management)."
	::= { gtmWideip 2 }

gtmWideipEntry OBJECT-TYPE
	SYNTAX  GtmWideipEntry
	MAX-ACCESS not-accessible
	STATUS current
	DESCRIPTION
		"Columns in the gtmWideip Table"
	INDEX {
		gtmWideipType,
		gtmWideipName
	}
	::= { gtmWideipTable 1 }

GtmWideipEntry ::=
	SEQUENCE {
        	gtmWideipName                                             LongDisplayString,
        	gtmWideipPersist                                          INTEGER,
        	gtmWideipTtlPersist                                       Gauge,
        	gtmWideipEnabled                                          INTEGER,
        	gtmWideipLbmodePool                                       INTEGER,
        	gtmWideipApplication                                      LongDisplayString,
        	gtmWideipLastResortPool                                   LongDisplayString,
        	gtmWideipIpNoError                                        INTEGER,
        	gtmWideipLoadBalancingDecisionLogVerbosity                Gauge,
        	gtmWideipIpNoErrorTtl                                     Gauge,
        	gtmWideipPersistCidr                                      Gauge,
        	gtmWideipPersistV6Cidr                                    Gauge,
        	gtmWideipMinimalResponse                                  INTEGER,
        	gtmWideipType                                             INTEGER,
        	gtmWideipLastResortPoolType                               INTEGER
	}

gtmWideipName OBJECT-TYPE
	SYNTAX LongDisplayString
	MAX-ACCESS read-only
	STATUS current
	DESCRIPTION
		"The name of a wide IP."
	::= { gtmWideipEntry 1 }

gtmWideipPersist OBJECT-TYPE
	SYNTAX INTEGER {
		false(0),
		true(1)
	}
	MAX-ACCESS read-only
	STATUS current
	DESCRIPTION
		"The state indicating whether or not to maintain a connection between
		a LDNS and a particular virtual server for the specified wide IP."
	::= { gtmWideipEntry 2 }

gtmWideipTtlPersist OBJECT-TYPE
	SYNTAX Gauge
	MAX-ACCESS read-only
	STATUS current
	DESCRIPTION
		"The persistence TTL value of the specified wide IP.
		This value (in seconds) indicates the time to maintain a connection
		between an LDNS and a particular virtual server."
	::= { gtmWideipEntry 3 }

gtmWideipEnabled OBJECT-TYPE
	SYNTAX INTEGER {
		disable(0),
		enable(1)
	}
	MAX-ACCESS read-only
	STATUS current
	DESCRIPTION
		"The state indicating whether the specified wide IP is enabled or not."
	::= { gtmWideipEntry 4 }

gtmWideipLbmodePool OBJECT-TYPE
	SYNTAX INTEGER {
		returntodns(0),
		null(1),
		roundrobin(2),
		ratio(3),
		topology(4),
		statpersit(5),
		ga(6),
		vscapacity(7),
		leastconn(8),
		lowestrtt(9),
		lowesthops(10),
		packetrate(11),
		cpu(12),
		hitratio(13),
		qos(14),
		bps(15),
		droppacket(16),
		explicitip(17),
		vsscore(18)
	}
	MAX-ACCESS read-only
	STATUS current
	DESCRIPTION
		"The load balancing method for the specified wide IP.
		This is used by the wide IPs when picking a pool to use when
		responding to a DNS request."
	::= { gtmWideipEntry 5 }

gtmWideipApplication OBJECT-TYPE
	SYNTAX LongDisplayString
	MAX-ACCESS read-only
	STATUS	 deprecated
	DESCRIPTION
		"Deprecated! No longer useful. Please use gtmApplicationWideip.
	        The application name the specified wide IP is used for."
	::= { gtmWideipEntry 6 }

gtmWideipLastResortPool OBJECT-TYPE
	SYNTAX LongDisplayString
	MAX-ACCESS read-only
	STATUS current
	DESCRIPTION
		"The name of the last-resort pool for the specified wide IP."
	::= { gtmWideipEntry 7 }

gtmWideipIpNoError OBJECT-TYPE
	SYNTAX INTEGER {
		disable(0),
		enable(1)
	}
	MAX-ACCESS read-only
	STATUS current
	DESCRIPTION
		"When enabled on a given wide IP, all requests sent to that
	        wide IP will be returned with a noerror response."
	::= { gtmWideipEntry 8 }

gtmWideipLoadBalancingDecisionLogVerbosity OBJECT-TYPE
	SYNTAX Gauge
	MAX-ACCESS read-only
	STATUS current
	DESCRIPTION
		"The log verbosity value when making load-balancing decisions. From
	        the least significant bit to the most significant bit, each bit
	        represents enabling or disabling a certain load balancing log. When the
	        first bit is 1, log will contain pool load-balancing algorithm
	        details. When the second bit is 1, log will contain details of all
	        pools traversed during load-balancing. When the third bit is 1, log
	        will contain pool member load-balancing algorithm details. When the
	        fourth bit is 1, log will contain details of all pool members
	        traversed during load-balancing."
	::= { gtmWideipEntry 9 }

gtmWideipIpNoErrorTtl OBJECT-TYPE
	SYNTAX Gauge
	MAX-ACCESS read-only
	STATUS current
	DESCRIPTION
		"The negative caching TTL of the SOA record for the NoError
	        response. The default is 0, which means that no SOA is included
	        (ie no caching)."
	::= { gtmWideipEntry 10 }

gtmWideipPersistCidr OBJECT-TYPE
	SYNTAX Gauge
	MAX-ACCESS read-only
	STATUS current
	DESCRIPTION
		"A mask used to group IPv4 LDNS addresses. This allows one
	        persistence record to be shared by IPv4 LDNS addresses that
	        match within this mask. The default is 32 (no shared
	        persistence records)."
	::= { gtmWideipEntry 11 }

gtmWideipPersistV6Cidr OBJECT-TYPE
	SYNTAX Gauge
	MAX-ACCESS read-only
	STATUS current
	DESCRIPTION
		"A mask used to group IPv6 LDNS addresses. This allows one
	        persistence record to be shared by IPv6 LDNS addresses that
	        match within this mask. The default is 128 (no shared
	        persistence records)."
	::= { gtmWideipEntry 12 }

gtmWideipMinimalResponse OBJECT-TYPE
	SYNTAX INTEGER {
		disable(0),
		enable(1)
	}
	MAX-ACCESS read-only
	STATUS current
	DESCRIPTION
		"Whether or not GTM will form the smallest allowable DNS
	        response to a query. The default is enabled. When set to
	        disabled, GTM will attempt to chase CNAME chains to obtain
	        the ultimate answer and attempt to add address resource
	        records to the additional section of the response for each
	        answer when needed."
	::= { gtmWideipEntry 13 }

gtmWideipType OBJECT-TYPE
	SYNTAX INTEGER {
		a(1),
		cname(5),
		mx(15),
		aaaa(28),
		srv(33),
		naptr(35)
	}
	MAX-ACCESS read-only
	STATUS current
	DESCRIPTION
		"The type of a wide IP."
	::= { gtmWideipEntry 14 }

gtmWideipLastResortPoolType OBJECT-TYPE
	SYNTAX INTEGER {
		a(1),
		cname(5),
		mx(15),
		aaaa(28),
		srv(33),
		naptr(35)
	}
	MAX-ACCESS read-only
	STATUS current
	DESCRIPTION
		"The type of the last-resort pool for the specified wide IP."
	::= { gtmWideipEntry 15 }

--==================================================================
-- Gtm_wideip_stat
--==================================================================
gtmWideipStatResetStats OBJECT-TYPE
	SYNTAX INTEGER
	MAX-ACCESS read-write
	STATUS current
	DESCRIPTION
		"The action to reset resettable statistics data in gtmWideipStat.
		 Setting this value to 1 will reset statistics data.
		 Note, some statistics data may not be reset including data that are incremental counters."
	::= { gtmWideipStat 1 }

gtmWideipStatNumber OBJECT-TYPE
	SYNTAX INTEGER
	MAX-ACCESS read-only
	STATUS current
	DESCRIPTION
		"The number of gtmWideipStat entries in the table."
	::= { gtmWideipStat 2 }

gtmWideipStatTable OBJECT-TYPE
	SYNTAX SEQUENCE OF GtmWideipStatEntry
	MAX-ACCESS not-accessible
	STATUS current
	DESCRIPTION
		"A table containing statistics information of wide IPs for GTM (Global Traffic Management)."
	::= { gtmWideipStat 3 }

gtmWideipStatEntry OBJECT-TYPE
	SYNTAX  GtmWideipStatEntry
	MAX-ACCESS not-accessible
	STATUS current
	DESCRIPTION
		"Columns in the gtmWideipStat Table"
	INDEX {
		gtmWideipStatWipType,
		gtmWideipStatName
	}
	::= { gtmWideipStatTable 1 }

GtmWideipStatEntry ::=
	SEQUENCE {
        	gtmWideipStatName                                         LongDisplayString,
        	gtmWideipStatRequests                                     Counter64,
        	gtmWideipStatResolutions                                  Counter64,
        	gtmWideipStatPersisted                                    Counter64,
        	gtmWideipStatPreferred                                    Counter64,
        	gtmWideipStatFallback                                     Counter64,
        	gtmWideipStatDropped                                      Counter64,
        	gtmWideipStatExplicitIp                                   Counter64,
        	gtmWideipStatReturnToDns                                  Counter64,
        	gtmWideipStatReturnFromDns                                Counter64,
        	gtmWideipStatCnameResolutions                             Counter64,
        	gtmWideipStatARequests                                    Counter64,
        	gtmWideipStatAaaaRequests                                 Counter64,
        	gtmWideipStatAlternate                                    Counter64,
        	gtmWideipStatWipType                                      INTEGER
	}

gtmWideipStatName OBJECT-TYPE
	SYNTAX LongDisplayString
	MAX-ACCESS read-only
	STATUS current
	DESCRIPTION
		"The name of the wide IP."
	::= { gtmWideipStatEntry 1 }

gtmWideipStatRequests OBJECT-TYPE
	SYNTAX Counter64
	MAX-ACCESS read-only
	STATUS current
	DESCRIPTION
		"The number of total requests for the specified wide IP."
	::= { gtmWideipStatEntry 2 }

gtmWideipStatResolutions OBJECT-TYPE
	SYNTAX Counter64
	MAX-ACCESS read-only
	STATUS current
	DESCRIPTION
		"The number of total resolutions for the specified wide IP."
	::= { gtmWideipStatEntry 3 }

gtmWideipStatPersisted OBJECT-TYPE
	SYNTAX Counter64
	MAX-ACCESS read-only
	STATUS current
	DESCRIPTION
		"The number of persisted requests for the specified wide IP."
	::= { gtmWideipStatEntry 4 }

gtmWideipStatPreferred OBJECT-TYPE
	SYNTAX Counter64
	MAX-ACCESS read-only
	STATUS current
	DESCRIPTION
		"The number of times which the preferred load balance method is used
		for the specified wide IP."
	::= { gtmWideipStatEntry 5 }

gtmWideipStatFallback OBJECT-TYPE
	SYNTAX Counter64
	MAX-ACCESS read-only
	STATUS current
	DESCRIPTION
		"The number of times which the fallback load balance method is used
	        for the specified wide IP."
	::= { gtmWideipStatEntry 6 }

gtmWideipStatDropped OBJECT-TYPE
	SYNTAX Counter64
	MAX-ACCESS read-only
	STATUS current
	DESCRIPTION
		"The number of dropped DNS messages for the specified wide IP."
	::= { gtmWideipStatEntry 7 }

gtmWideipStatExplicitIp OBJECT-TYPE
	SYNTAX Counter64
	MAX-ACCESS read-only
	STATUS	 deprecated
	DESCRIPTION
		"Deprecated! The number of times which a LDNS  was persisted to the
	        specified wide IP by the explicit IP rule."
	::= { gtmWideipStatEntry 8 }

gtmWideipStatReturnToDns OBJECT-TYPE
	SYNTAX Counter64
	MAX-ACCESS read-only
	STATUS current
	DESCRIPTION
		"The number of times which a resolve was returned to DNS (for resolution)
		for the specified wide IP."
	::= { gtmWideipStatEntry 9 }

gtmWideipStatReturnFromDns OBJECT-TYPE
	SYNTAX Counter64
	MAX-ACCESS read-only
	STATUS current
	DESCRIPTION
		"The number of times which a resolve was returned from DNS for the
	        specified wide IP."
	::= { gtmWideipStatEntry 10 }

gtmWideipStatCnameResolutions OBJECT-TYPE
	SYNTAX Counter64
	MAX-ACCESS read-only
	STATUS current
	DESCRIPTION
		"The number of times which a query is resolved by the CNAME of pools
	        associated with the specified Wide IP."
	::= { gtmWideipStatEntry 11 }

gtmWideipStatARequests OBJECT-TYPE
	SYNTAX Counter64
	MAX-ACCESS read-only
	STATUS	 deprecated
	DESCRIPTION
		"Deprecated! No longer used.
	        The number of A requests for the specified wide IP."
	::= { gtmWideipStatEntry 12 }

gtmWideipStatAaaaRequests OBJECT-TYPE
	SYNTAX Counter64
	MAX-ACCESS read-only
	STATUS	 deprecated
	DESCRIPTION
		"Deprecated! No longer used.
	        The number of AAAA requests for the specified wide IP."
	::= { gtmWideipStatEntry 13 }

gtmWideipStatAlternate OBJECT-TYPE
	SYNTAX Counter64
	MAX-ACCESS read-only
	STATUS current
	DESCRIPTION
		"The number of times which the alternate load balance method is used
	        for the specified wide IP."
	::= { gtmWideipStatEntry 14 }

gtmWideipStatWipType OBJECT-TYPE
	SYNTAX INTEGER {
		a(1),
		cname(5),
		mx(15),
		aaaa(28),
		srv(33),
		naptr(35)
	}
	MAX-ACCESS read-only
	STATUS current
	DESCRIPTION
		"The type of the wide IP."
	::= { gtmWideipStatEntry 15 }

--==================================================================
-- Gtm_wideip_status
--==================================================================
gtmWideipStatusNumber OBJECT-TYPE
	SYNTAX INTEGER
	MAX-ACCESS read-only
	STATUS current
	DESCRIPTION
		"The number of gtmWideipStatus entries in the table."
	::= { gtmWideipStatus 1 }

gtmWideipStatusTable OBJECT-TYPE
	SYNTAX SEQUENCE OF GtmWideipStatusEntry
	MAX-ACCESS not-accessible
	STATUS current
	DESCRIPTION
		"A table containing status information of wide IPs for GTM (Global Traffic Management)."
	::= { gtmWideipStatus 2 }

gtmWideipStatusEntry OBJECT-TYPE
	SYNTAX  GtmWideipStatusEntry
	MAX-ACCESS not-accessible
	STATUS current
	DESCRIPTION
		"Columns in the gtmWideipStatus Table"
	INDEX {
		gtmWideipStatusType,
		gtmWideipStatusName
	}
	::= { gtmWideipStatusTable 1 }

GtmWideipStatusEntry ::=
	SEQUENCE {
        	gtmWideipStatusName                                       LongDisplayString,
        	gtmWideipStatusAvailState                                 INTEGER,
        	gtmWideipStatusEnabledState                               INTEGER,
        	gtmWideipStatusParentType                                 Gauge,
        	gtmWideipStatusDetailReason                               LongDisplayString,
        	gtmWideipStatusType                                       INTEGER
	}

gtmWideipStatusName OBJECT-TYPE
	SYNTAX LongDisplayString
	MAX-ACCESS read-only
	STATUS current
	DESCRIPTION
		"The name of a wide IP."
	::= { gtmWideipStatusEntry 1 }

gtmWideipStatusAvailState OBJECT-TYPE
	SYNTAX INTEGER {
		none(0),
		green(1),
		yellow(2),
		red(3),
		blue(4),
		gray(5)
	}
	MAX-ACCESS read-only
	STATUS current
	DESCRIPTION
		"The availability of the specified wide IP indicated by color.
		none - error;
		green - available in some capacity;
		yellow - not currently available;
		red - not available;
		blue - availability is unknown;
		gray - unlicensed."
	::= { gtmWideipStatusEntry 2 }

gtmWideipStatusEnabledState OBJECT-TYPE
	SYNTAX INTEGER {
		none(0),
		enabled(1),
		disabled(2),
		disabledbyparent(3)
	}
	MAX-ACCESS read-only
	STATUS current
	DESCRIPTION
		"The activity status of the specified wide IP, as specified
		by the user."
	::= { gtmWideipStatusEntry 3 }

gtmWideipStatusParentType OBJECT-TYPE
	SYNTAX Gauge
	MAX-ACCESS read-only
	STATUS	 deprecated
	DESCRIPTION
		"Deprecated! This is an internal data.
		The type of parent object which disabled the specified wide IP."
	::= { gtmWideipStatusEntry 4 }

gtmWideipStatusDetailReason OBJECT-TYPE
	SYNTAX LongDisplayString
	MAX-ACCESS read-only
	STATUS current
	DESCRIPTION
		"The detail description of the specified wide IP's status."
	::= { gtmWideipStatusEntry 5 }

gtmWideipStatusType OBJECT-TYPE
	SYNTAX INTEGER {
		a(1),
		cname(5),
		mx(15),
		aaaa(28),
		srv(33),
		naptr(35)
	}
	MAX-ACCESS read-only
	STATUS current
	DESCRIPTION
		"The type of a wide IP."
	::= { gtmWideipStatusEntry 6 }

--==================================================================
-- Gtm_wideip_alias
--==================================================================
gtmWideipAliasNumber OBJECT-TYPE
	SYNTAX INTEGER
	MAX-ACCESS read-only
	STATUS current
	DESCRIPTION
		"The number of gtmWideipAlias entries in the table."
	::= { gtmWideipAlias 1 }

gtmWideipAliasTable OBJECT-TYPE
	SYNTAX SEQUENCE OF GtmWideipAliasEntry
	MAX-ACCESS not-accessible
	STATUS current
	DESCRIPTION
		"A table containing information of aliases of the specified wide IPs
		for GTM (Global Traffic Management)."
	::= { gtmWideipAlias 2 }

gtmWideipAliasEntry OBJECT-TYPE
	SYNTAX  GtmWideipAliasEntry
	MAX-ACCESS not-accessible
	STATUS current
	DESCRIPTION
		"Columns in the gtmWideipAlias Table"
	INDEX {
		gtmWideipAliasWipType,
		gtmWideipAliasWipName,
		gtmWideipAliasName
	}
	::= { gtmWideipAliasTable 1 }

GtmWideipAliasEntry ::=
	SEQUENCE {
        	gtmWideipAliasWipName                                     LongDisplayString,
        	gtmWideipAliasName                                        LongDisplayString,
        	gtmWideipAliasWipType                                     INTEGER
	}

gtmWideipAliasWipName OBJECT-TYPE
	SYNTAX LongDisplayString
	MAX-ACCESS read-only
	STATUS current
	DESCRIPTION
		"The name of the wide IP."
	::= { gtmWideipAliasEntry 1 }

gtmWideipAliasName OBJECT-TYPE
	SYNTAX LongDisplayString
	MAX-ACCESS read-only
	STATUS current
	DESCRIPTION
		"The alias name of the specified wide IP."
	::= { gtmWideipAliasEntry 2 }

gtmWideipAliasWipType OBJECT-TYPE
	SYNTAX INTEGER {
		a(1),
		cname(5),
		mx(15),
		aaaa(28),
		srv(33),
		naptr(35)
	}
	MAX-ACCESS read-only
	STATUS current
	DESCRIPTION
		"The type of the wide IP."
	::= { gtmWideipAliasEntry 3 }

--==================================================================
-- Gtm_wideip_pool
--==================================================================
gtmWideipPoolNumber OBJECT-TYPE
	SYNTAX INTEGER
	MAX-ACCESS read-only
	STATUS current
	DESCRIPTION
		"The number of gtmWideipPool entries in the table."
	::= { gtmWideipPool 1 }

gtmWideipPoolTable OBJECT-TYPE
	SYNTAX SEQUENCE OF GtmWideipPoolEntry
	MAX-ACCESS not-accessible
	STATUS current
	DESCRIPTION
		"A table containing information of pools associated with
		the specified wide IPs for GTM (Global Traffic Management)."
	::= { gtmWideipPool 2 }

gtmWideipPoolEntry OBJECT-TYPE
	SYNTAX  GtmWideipPoolEntry
	MAX-ACCESS not-accessible
	STATUS current
	DESCRIPTION
		"Columns in the gtmWideipPool Table"
	INDEX {
		gtmWideipPoolWipType,
		gtmWideipPoolWipName,
		gtmWideipPoolPoolType,
		gtmWideipPoolPoolName
	}
	::= { gtmWideipPoolTable 1 }

GtmWideipPoolEntry ::=
	SEQUENCE {
        	gtmWideipPoolWipName                                      LongDisplayString,
        	gtmWideipPoolPoolName                                     LongDisplayString,
        	gtmWideipPoolOrder                                        INTEGER,
        	gtmWideipPoolRatio                                        INTEGER,
        	gtmWideipPoolWipType                                      INTEGER,
        	gtmWideipPoolPoolType                                     INTEGER
	}

gtmWideipPoolWipName OBJECT-TYPE
	SYNTAX LongDisplayString
	MAX-ACCESS read-only
	STATUS current
	DESCRIPTION
		"The name of the wide IP."
	::= { gtmWideipPoolEntry 1 }

gtmWideipPoolPoolName OBJECT-TYPE
	SYNTAX LongDisplayString
	MAX-ACCESS read-only
	STATUS current
	DESCRIPTION
		"The name of the pool which associates with the specified wide IP."
	::= { gtmWideipPoolEntry 2 }

gtmWideipPoolOrder OBJECT-TYPE
	SYNTAX INTEGER
	MAX-ACCESS read-only
	STATUS current
	DESCRIPTION
		"This determines order of pools in wip. zero-based."
	::= { gtmWideipPoolEntry 3 }

gtmWideipPoolRatio OBJECT-TYPE
	SYNTAX INTEGER
	MAX-ACCESS read-only
	STATUS current
	DESCRIPTION
		"The load balancing ratio given to the specified pool."
	::= { gtmWideipPoolEntry 4 }

gtmWideipPoolWipType OBJECT-TYPE
	SYNTAX INTEGER {
		a(1),
		cname(5),
		mx(15),
		aaaa(28),
		srv(33),
		naptr(35)
	}
	MAX-ACCESS read-only
	STATUS current
	DESCRIPTION
		"The type of the wide IP."
	::= { gtmWideipPoolEntry 5 }

gtmWideipPoolPoolType OBJECT-TYPE
	SYNTAX INTEGER {
		a(1),
		cname(5),
		mx(15),
		aaaa(28),
		srv(33),
		naptr(35)
	}
	MAX-ACCESS read-only
	STATUS current
	DESCRIPTION
		"The type of the pool."
	::= { gtmWideipPoolEntry 6 }

--==================================================================
-- Gtm_wideip_rule
--==================================================================
gtmWideipRuleNumber OBJECT-TYPE
	SYNTAX INTEGER
	MAX-ACCESS read-only
	STATUS current
	DESCRIPTION
		"The number of gtmWideipRule entries in the table."
	::= { gtmWideipRule 1 }

gtmWideipRuleTable OBJECT-TYPE
	SYNTAX SEQUENCE OF GtmWideipRuleEntry
	MAX-ACCESS not-accessible
	STATUS current
	DESCRIPTION
		"A table containing information of rules associated with
		the specified wide IPs for GTM (Global Traffic Management)."
	::= { gtmWideipRule 2 }

gtmWideipRuleEntry OBJECT-TYPE
	SYNTAX  GtmWideipRuleEntry
	MAX-ACCESS not-accessible
	STATUS current
	DESCRIPTION
		"Columns in the gtmWideipRule Table"
	INDEX {
		gtmWideipRuleWipType,
		gtmWideipRuleWipName,
		gtmWideipRuleRuleName
	}
	::= { gtmWideipRuleTable 1 }

GtmWideipRuleEntry ::=
	SEQUENCE {
        	gtmWideipRuleWipName                                      LongDisplayString,
        	gtmWideipRuleRuleName                                     LongDisplayString,
        	gtmWideipRulePriority                                     Gauge,
        	gtmWideipRuleWipType                                      INTEGER
	}

gtmWideipRuleWipName OBJECT-TYPE
	SYNTAX LongDisplayString
	MAX-ACCESS read-only
	STATUS current
	DESCRIPTION
		"The name of the wide IP."
	::= { gtmWideipRuleEntry 1 }

gtmWideipRuleRuleName OBJECT-TYPE
	SYNTAX LongDisplayString
	MAX-ACCESS read-only
	STATUS current
	DESCRIPTION
		"The name of the rule which associates with the specified wide IP."
	::= { gtmWideipRuleEntry 2 }

gtmWideipRulePriority OBJECT-TYPE
	SYNTAX Gauge
	MAX-ACCESS read-only
	STATUS current
	DESCRIPTION
		"The execution priority of the rule for the specified wide IP."
	::= { gtmWideipRuleEntry 3 }

gtmWideipRuleWipType OBJECT-TYPE
	SYNTAX INTEGER {
		a(1),
		cname(5),
		mx(15),
		aaaa(28),
		srv(33),
		naptr(35)
	}
	MAX-ACCESS read-only
	STATUS current
	DESCRIPTION
		"The type of the wide IP."
	::= { gtmWideipRuleEntry 4 }

--==================================================================
-- Gtm_server_stat2
--==================================================================
gtmServerStat2ResetStats OBJECT-TYPE
	SYNTAX INTEGER
	MAX-ACCESS read-write
	STATUS current
	DESCRIPTION
		"The action to reset resettable statistics data in gtmServerStat2.
		 Setting this value to 1 will reset statistics data.
		 Note, some statistics data may not be reset including data that are incremental counters."
	::= { gtmServerStat2 1 }

gtmServerStat2Number OBJECT-TYPE
	SYNTAX INTEGER
	MAX-ACCESS read-only
	STATUS current
	DESCRIPTION
		"The number of gtmServerStat2 entries in the table."
	::= { gtmServerStat2 2 }

gtmServerStat2Table OBJECT-TYPE
	SYNTAX SEQUENCE OF GtmServerStat2Entry
	MAX-ACCESS not-accessible
	STATUS current
	DESCRIPTION
		"A table containing statistics information of servers within associated
		 data center for GTM (Global Traffic Management)."
	::= { gtmServerStat2 3 }

gtmServerStat2Entry OBJECT-TYPE
	SYNTAX  GtmServerStat2Entry
	MAX-ACCESS not-accessible
	STATUS current
	DESCRIPTION
		"Columns in the gtmServerStat2 Table"
	INDEX {
		gtmServerStat2Name
	}
	::= { gtmServerStat2Table 1 }

GtmServerStat2Entry ::=
	SEQUENCE {
        	gtmServerStat2Name                                        LongDisplayString,
        	gtmServerStat2UnitId                                      INTEGER,
        	gtmServerStat2VsPicks                                     Counter64,
        	gtmServerStat2CpuUsage                                    Counter64,
        	gtmServerStat2MemAvail                                    Counter64,
        	gtmServerStat2BitsPerSecIn                                Counter64,
        	gtmServerStat2BitsPerSecOut                               Counter64,
        	gtmServerStat2PktsPerSecIn                                Counter64,
        	gtmServerStat2PktsPerSecOut                               Counter64,
        	gtmServerStat2Connections                                 Counter64,
        	gtmServerStat2ConnRate                                    Counter64
	}

gtmServerStat2Name OBJECT-TYPE
	SYNTAX LongDisplayString
	MAX-ACCESS read-only
	STATUS current
	DESCRIPTION
		"The name of a server."
	::= { gtmServerStat2Entry 1 }

gtmServerStat2UnitId OBJECT-TYPE
	SYNTAX INTEGER
	MAX-ACCESS read-only
	STATUS	 deprecated
	DESCRIPTION
		"Deprecated! This feature has been eliminated.
		The unit ID of the specified server."
	::= { gtmServerStat2Entry 2 }

gtmServerStat2VsPicks OBJECT-TYPE
	SYNTAX Counter64
	MAX-ACCESS read-only
	STATUS current
	DESCRIPTION
		"How many times a virtual server of the specified server was picked
		during resolution of a domain name. I.E amazon.com got resolved to
		a particular virtual address X times."
	::= { gtmServerStat2Entry 3 }

gtmServerStat2CpuUsage OBJECT-TYPE
	SYNTAX Counter64
	MAX-ACCESS read-only
	STATUS current
	DESCRIPTION
		"The CPU usage in percentage for the specified server."
	::= { gtmServerStat2Entry 4 }

gtmServerStat2MemAvail OBJECT-TYPE
	SYNTAX Counter64
	MAX-ACCESS read-only
	STATUS current
	DESCRIPTION
		"The memory available in bytes for the specified server."
	::= { gtmServerStat2Entry 5 }

gtmServerStat2BitsPerSecIn OBJECT-TYPE
	SYNTAX Counter64
	MAX-ACCESS read-only
	STATUS current
	DESCRIPTION
		"The number of bits per second received by the specified server."
	::= { gtmServerStat2Entry 6 }

gtmServerStat2BitsPerSecOut OBJECT-TYPE
	SYNTAX Counter64
	MAX-ACCESS read-only
	STATUS current
	DESCRIPTION
		"The number of bits per second sent from the specified server."
	::= { gtmServerStat2Entry 7 }

gtmServerStat2PktsPerSecIn OBJECT-TYPE
	SYNTAX Counter64
	MAX-ACCESS read-only
	STATUS current
	DESCRIPTION
		"The number of packets per second received by the specified server."
	::= { gtmServerStat2Entry 8 }

gtmServerStat2PktsPerSecOut OBJECT-TYPE
	SYNTAX Counter64
	MAX-ACCESS read-only
	STATUS current
	DESCRIPTION
		"The number of packets per second sent from the specified server."
	::= { gtmServerStat2Entry 9 }

gtmServerStat2Connections OBJECT-TYPE
	SYNTAX Counter64
	MAX-ACCESS read-only
	STATUS current
	DESCRIPTION
		"The number of total connections to the specified server."
	::= { gtmServerStat2Entry 10 }

gtmServerStat2ConnRate OBJECT-TYPE
	SYNTAX Counter64
	MAX-ACCESS read-only
	STATUS	 deprecated
	DESCRIPTION
		"Deprecated! This feature has been eliminated.
		The connection rate (current connection rate/connection rate limit)
		in percentage for the specified server."
	::= { gtmServerStat2Entry 11 }

--==================================================================
-- Gtm_prober_pool
--==================================================================
gtmProberPoolNumber OBJECT-TYPE
	SYNTAX INTEGER
	MAX-ACCESS read-only
	STATUS current
	DESCRIPTION
		"The number of gtmProberPool entries in the table."
	::= { gtmProberPool 1 }

gtmProberPoolTable OBJECT-TYPE
	SYNTAX SEQUENCE OF GtmProberPoolEntry
	MAX-ACCESS not-accessible
	STATUS current
	DESCRIPTION
		"A table containing information for GTM prober pools."
	::= { gtmProberPool 2 }

gtmProberPoolEntry OBJECT-TYPE
	SYNTAX  GtmProberPoolEntry
	MAX-ACCESS not-accessible
	STATUS current
	DESCRIPTION
		"Columns in the gtmProberPool Table"
	INDEX {
		gtmProberPoolName
	}
	::= { gtmProberPoolTable 1 }

GtmProberPoolEntry ::=
	SEQUENCE {
        	gtmProberPoolName                                         LongDisplayString,
        	gtmProberPoolLbMode                                       INTEGER,
        	gtmProberPoolEnabled                                      INTEGER
	}

gtmProberPoolName OBJECT-TYPE
	SYNTAX LongDisplayString
	MAX-ACCESS read-only
	STATUS current
	DESCRIPTION
		"The name of a prober pool."
	::= { gtmProberPoolEntry 1 }

gtmProberPoolLbMode OBJECT-TYPE
	SYNTAX INTEGER {
		roundrobin(2),
		ga(6)
	}
	MAX-ACCESS read-only
	STATUS current
	DESCRIPTION
		"The preferred load balancing method for the specified prober pool."
	::= { gtmProberPoolEntry 2 }

gtmProberPoolEnabled OBJECT-TYPE
	SYNTAX INTEGER {
		false(0),
		true(1)
	}
	MAX-ACCESS read-only
	STATUS current
	DESCRIPTION
		"The state indicating whether the specified prober pool is enabled or not."
	::= { gtmProberPoolEntry 3 }

--==================================================================
-- Gtm_prober_pool_stat
--==================================================================
gtmProberPoolStatResetStats OBJECT-TYPE
	SYNTAX INTEGER
	MAX-ACCESS read-write
	STATUS current
	DESCRIPTION
		"The action to reset resettable statistics data in gtmProberPoolStat.
		 Setting this value to 1 will reset statistics data.
		 Note, some statistics data may not be reset including data that are incremental counters."
	::= { gtmProberPoolStat 1 }

gtmProberPoolStatNumber OBJECT-TYPE
	SYNTAX INTEGER
	MAX-ACCESS read-only
	STATUS current
	DESCRIPTION
		"The number of gtmProberPoolStat entries in the table."
	::= { gtmProberPoolStat 2 }

gtmProberPoolStatTable OBJECT-TYPE
	SYNTAX SEQUENCE OF GtmProberPoolStatEntry
	MAX-ACCESS not-accessible
	STATUS current
	DESCRIPTION
		"A table containing statistics information for GTM prober pools."
	::= { gtmProberPoolStat 3 }

gtmProberPoolStatEntry OBJECT-TYPE
	SYNTAX  GtmProberPoolStatEntry
	MAX-ACCESS not-accessible
	STATUS current
	DESCRIPTION
		"Columns in the gtmProberPoolStat Table"
	INDEX {
		gtmProberPoolStatName
	}
	::= { gtmProberPoolStatTable 1 }

GtmProberPoolStatEntry ::=
	SEQUENCE {
        	gtmProberPoolStatName                                     LongDisplayString,
        	gtmProberPoolStatTotalProbes                              Counter64,
        	gtmProberPoolStatSuccessfulProbes                         Counter64,
        	gtmProberPoolStatFailedProbes                             Counter64
	}

gtmProberPoolStatName OBJECT-TYPE
	SYNTAX LongDisplayString
	MAX-ACCESS read-only
	STATUS current
	DESCRIPTION
		"The name of a prober pool."
	::= { gtmProberPoolStatEntry 1 }

gtmProberPoolStatTotalProbes OBJECT-TYPE
	SYNTAX Counter64
	MAX-ACCESS read-only
	STATUS current
	DESCRIPTION
		"The number of total probes."
	::= { gtmProberPoolStatEntry 2 }

gtmProberPoolStatSuccessfulProbes OBJECT-TYPE
	SYNTAX Counter64
	MAX-ACCESS read-only
	STATUS current
	DESCRIPTION
		"The number of successful probes."
	::= { gtmProberPoolStatEntry 3 }

gtmProberPoolStatFailedProbes OBJECT-TYPE
	SYNTAX Counter64
	MAX-ACCESS read-only
	STATUS current
	DESCRIPTION
		"The number of failed probes."
	::= { gtmProberPoolStatEntry 4 }

--==================================================================
-- Gtm_prober_pool_status
--==================================================================
gtmProberPoolStatusNumber OBJECT-TYPE
	SYNTAX INTEGER
	MAX-ACCESS read-only
	STATUS current
	DESCRIPTION
		"The number of gtmProberPoolStatus entries in the table."
	::= { gtmProberPoolStatus 1 }

gtmProberPoolStatusTable OBJECT-TYPE
	SYNTAX SEQUENCE OF GtmProberPoolStatusEntry
	MAX-ACCESS not-accessible
	STATUS current
	DESCRIPTION
		"A table containing status information for GTM prober pools."
	::= { gtmProberPoolStatus 2 }

gtmProberPoolStatusEntry OBJECT-TYPE
	SYNTAX  GtmProberPoolStatusEntry
	MAX-ACCESS not-accessible
	STATUS current
	DESCRIPTION
		"Columns in the gtmProberPoolStatus Table"
	INDEX {
		gtmProberPoolStatusName
	}
	::= { gtmProberPoolStatusTable 1 }

GtmProberPoolStatusEntry ::=
	SEQUENCE {
        	gtmProberPoolStatusName                                   LongDisplayString,
        	gtmProberPoolStatusAvailState                             INTEGER,
        	gtmProberPoolStatusEnabledState                           INTEGER,
        	gtmProberPoolStatusDetailReason                           LongDisplayString
	}

gtmProberPoolStatusName OBJECT-TYPE
	SYNTAX LongDisplayString
	MAX-ACCESS read-only
	STATUS current
	DESCRIPTION
		"The name of a prober pool."
	::= { gtmProberPoolStatusEntry 1 }

gtmProberPoolStatusAvailState OBJECT-TYPE
	SYNTAX INTEGER {
		none(0),
		green(1),
		yellow(2),
		red(3),
		blue(4),
		gray(5)
	}
	MAX-ACCESS read-only
	STATUS current
	DESCRIPTION
		"The availability of the specified pool indicated by color.
		none - error;
		green - available;
		yellow - not currently available;
		red - not available;
		blue - availability is unknown;
		gray - unlicensed."
	::= { gtmProberPoolStatusEntry 2 }

gtmProberPoolStatusEnabledState OBJECT-TYPE
	SYNTAX INTEGER {
		none(0),
		enabled(1),
		disabled(2),
		disabledbyparent(3)
	}
	MAX-ACCESS read-only
	STATUS current
	DESCRIPTION
		"The activity status of the specified pool, as specified
		by the user."
	::= { gtmProberPoolStatusEntry 3 }

gtmProberPoolStatusDetailReason OBJECT-TYPE
	SYNTAX LongDisplayString
	MAX-ACCESS read-only
	STATUS current
	DESCRIPTION
		"The detail description of the specified pool's status."
	::= { gtmProberPoolStatusEntry 4 }

--==================================================================
-- Gtm_prober_pool_member
--==================================================================
gtmProberPoolMbrNumber OBJECT-TYPE
	SYNTAX INTEGER
	MAX-ACCESS read-only
	STATUS current
	DESCRIPTION
		"The number of gtmProberPoolMember entries in the table."
	::= { gtmProberPoolMember 1 }

gtmProberPoolMbrTable OBJECT-TYPE
	SYNTAX SEQUENCE OF GtmProberPoolMbrEntry
	MAX-ACCESS not-accessible
	STATUS current
	DESCRIPTION
		"A table containing information for GTM prober pool members."
	::= { gtmProberPoolMember 2 }

gtmProberPoolMbrEntry OBJECT-TYPE
	SYNTAX  GtmProberPoolMbrEntry
	MAX-ACCESS not-accessible
	STATUS current
	DESCRIPTION
		"Columns in the gtmProberPoolMbr Table"
	INDEX {
		gtmProberPoolMbrPoolName,
		gtmProberPoolMbrServerName
	}
	::= { gtmProberPoolMbrTable 1 }

GtmProberPoolMbrEntry ::=
	SEQUENCE {
        	gtmProberPoolMbrPoolName                                  LongDisplayString,
        	gtmProberPoolMbrServerName                                LongDisplayString,
        	gtmProberPoolMbrPmbrOrder                                 INTEGER,
        	gtmProberPoolMbrEnabled                                   INTEGER
	}

gtmProberPoolMbrPoolName OBJECT-TYPE
	SYNTAX LongDisplayString
	MAX-ACCESS read-only
	STATUS current
	DESCRIPTION
		"The name of a prober pool."
	::= { gtmProberPoolMbrEntry 1 }

gtmProberPoolMbrServerName OBJECT-TYPE
	SYNTAX LongDisplayString
	MAX-ACCESS read-only
	STATUS current
	DESCRIPTION
		"The name of a server."
	::= { gtmProberPoolMbrEntry 2 }

gtmProberPoolMbrPmbrOrder OBJECT-TYPE
	SYNTAX INTEGER
	MAX-ACCESS read-only
	STATUS current
	DESCRIPTION
		"The prober pool member order."
	::= { gtmProberPoolMbrEntry 3 }

gtmProberPoolMbrEnabled OBJECT-TYPE
	SYNTAX INTEGER {
		false(0),
		true(1)
	}
	MAX-ACCESS read-only
	STATUS current
	DESCRIPTION
		"The state indicating whether the specified prober pool member
		is enabled or not."
	::= { gtmProberPoolMbrEntry 4 }

--==================================================================
-- Gtm_prober_pool_member_stat
--==================================================================
gtmProberPoolMbrStatResetStats OBJECT-TYPE
	SYNTAX INTEGER
	MAX-ACCESS read-write
	STATUS current
	DESCRIPTION
		"The action to reset resettable statistics data in gtmProberPoolMemberStat.
		 Setting this value to 1 will reset statistics data.
		 Note, some statistics data may not be reset including data that are incremental counters."
	::= { gtmProberPoolMemberStat 1 }

gtmProberPoolMbrStatNumber OBJECT-TYPE
	SYNTAX INTEGER
	MAX-ACCESS read-only
	STATUS current
	DESCRIPTION
		"The number of gtmProberPoolMemberStat entries in the table."
	::= { gtmProberPoolMemberStat 2 }

gtmProberPoolMbrStatTable OBJECT-TYPE
	SYNTAX SEQUENCE OF GtmProberPoolMbrStatEntry
	MAX-ACCESS not-accessible
	STATUS current
	DESCRIPTION
		"A table containing statistics information for GTM prober pool members."
	::= { gtmProberPoolMemberStat 3 }

gtmProberPoolMbrStatEntry OBJECT-TYPE
	SYNTAX  GtmProberPoolMbrStatEntry
	MAX-ACCESS not-accessible
	STATUS current
	DESCRIPTION
		"Columns in the gtmProberPoolMbrStat Table"
	INDEX {
		gtmProberPoolMbrStatPoolName,
		gtmProberPoolMbrStatServerName
	}
	::= { gtmProberPoolMbrStatTable 1 }

GtmProberPoolMbrStatEntry ::=
	SEQUENCE {
        	gtmProberPoolMbrStatPoolName                              LongDisplayString,
        	gtmProberPoolMbrStatServerName                            LongDisplayString,
        	gtmProberPoolMbrStatTotalProbes                           Counter64,
        	gtmProberPoolMbrStatSuccessfulProbes                      Counter64,
        	gtmProberPoolMbrStatFailedProbes                          Counter64
	}

gtmProberPoolMbrStatPoolName OBJECT-TYPE
	SYNTAX LongDisplayString
	MAX-ACCESS read-only
	STATUS current
	DESCRIPTION
		"The name of a prober pool."
	::= { gtmProberPoolMbrStatEntry 1 }

gtmProberPoolMbrStatServerName OBJECT-TYPE
	SYNTAX LongDisplayString
	MAX-ACCESS read-only
	STATUS current
	DESCRIPTION
		"The name of a server."
	::= { gtmProberPoolMbrStatEntry 2 }

gtmProberPoolMbrStatTotalProbes OBJECT-TYPE
	SYNTAX Counter64
	MAX-ACCESS read-only
	STATUS current
	DESCRIPTION
		"The number of total probes issued by this pool member."
	::= { gtmProberPoolMbrStatEntry 3 }

gtmProberPoolMbrStatSuccessfulProbes OBJECT-TYPE
	SYNTAX Counter64
	MAX-ACCESS read-only
	STATUS current
	DESCRIPTION
		"The number of successful probes issued by this pool member."
	::= { gtmProberPoolMbrStatEntry 4 }

gtmProberPoolMbrStatFailedProbes OBJECT-TYPE
	SYNTAX Counter64
	MAX-ACCESS read-only
	STATUS current
	DESCRIPTION
		"The number of failed probes issued by pool member."
	::= { gtmProberPoolMbrStatEntry 5 }

--==================================================================
-- Gtm_prober_pool_member_status
--==================================================================
gtmProberPoolMbrStatusNumber OBJECT-TYPE
	SYNTAX INTEGER
	MAX-ACCESS read-only
	STATUS current
	DESCRIPTION
		"The number of gtmProberPoolMemberStatus entries in the table."
	::= { gtmProberPoolMemberStatus 1 }

gtmProberPoolMbrStatusTable OBJECT-TYPE
	SYNTAX SEQUENCE OF GtmProberPoolMbrStatusEntry
	MAX-ACCESS not-accessible
	STATUS current
	DESCRIPTION
		"A table containing status information for GTM prober pool members."
	::= { gtmProberPoolMemberStatus 2 }

gtmProberPoolMbrStatusEntry OBJECT-TYPE
	SYNTAX  GtmProberPoolMbrStatusEntry
	MAX-ACCESS not-accessible
	STATUS current
	DESCRIPTION
		"Columns in the gtmProberPoolMbrStatus Table"
	INDEX {
		gtmProberPoolMbrStatusPoolName,
		gtmProberPoolMbrStatusServerName
	}
	::= { gtmProberPoolMbrStatusTable 1 }

GtmProberPoolMbrStatusEntry ::=
	SEQUENCE {
        	gtmProberPoolMbrStatusPoolName                            LongDisplayString,
        	gtmProberPoolMbrStatusServerName                          LongDisplayString,
        	gtmProberPoolMbrStatusAvailState                          INTEGER,
        	gtmProberPoolMbrStatusEnabledState                        INTEGER,
        	gtmProberPoolMbrStatusDetailReason                        LongDisplayString
	}

gtmProberPoolMbrStatusPoolName OBJECT-TYPE
	SYNTAX LongDisplayString
	MAX-ACCESS read-only
	STATUS current
	DESCRIPTION
		"The name of a prober pool."
	::= { gtmProberPoolMbrStatusEntry 1 }

gtmProberPoolMbrStatusServerName OBJECT-TYPE
	SYNTAX LongDisplayString
	MAX-ACCESS read-only
	STATUS current
	DESCRIPTION
		"The name of a server."
	::= { gtmProberPoolMbrStatusEntry 2 }

gtmProberPoolMbrStatusAvailState OBJECT-TYPE
	SYNTAX INTEGER {
		none(0),
		green(1),
		yellow(2),
		red(3),
		blue(4),
		gray(5)
	}
	MAX-ACCESS read-only
	STATUS current
	DESCRIPTION
		"The availability of the specified pool member indicated by color.
		none - error;
		green - available;
		yellow - not currently available;
		red - not available;
		blue - availability is unknown;
		gray - unlicensed."
	::= { gtmProberPoolMbrStatusEntry 3 }

gtmProberPoolMbrStatusEnabledState OBJECT-TYPE
	SYNTAX INTEGER {
		none(0),
		enabled(1),
		disabled(2),
		disabledbyparent(3)
	}
	MAX-ACCESS read-only
	STATUS current
	DESCRIPTION
		"The activity status of the specified pool member, as specified
		by the user."
	::= { gtmProberPoolMbrStatusEntry 4 }

gtmProberPoolMbrStatusDetailReason OBJECT-TYPE
	SYNTAX LongDisplayString
	MAX-ACCESS read-only
	STATUS current
	DESCRIPTION
		"The detail description of the specified pool member's status."
	::= { gtmProberPoolMbrStatusEntry 5 }

--==================================================================
-- Gtm_globals2
--==================================================================
gtmAttr2Number OBJECT-TYPE
	SYNTAX INTEGER
	MAX-ACCESS read-only
	STATUS current
	DESCRIPTION
		"The number of gtmGlobalAttr2 entries in the table."
	::= { gtmGlobalAttr2 1 }

gtmAttr2Table OBJECT-TYPE
	SYNTAX SEQUENCE OF GtmAttr2Entry
	MAX-ACCESS not-accessible
	STATUS current
	DESCRIPTION
		"The information of the global attributes for GTM (Global Traffic Management)."
	::= { gtmGlobalAttr2 2 }

gtmAttr2Entry OBJECT-TYPE
	SYNTAX  GtmAttr2Entry
	MAX-ACCESS not-accessible
	STATUS current
	DESCRIPTION
		"Columns in the gtmAttr2 Table"
	INDEX {
		gtmAttr2Name
	}
	::= { gtmAttr2Table 1 }

GtmAttr2Entry ::=
	SEQUENCE {
        	gtmAttr2DumpTopology                                      INTEGER,
        	gtmAttr2CacheLdns                                         INTEGER,
        	gtmAttr2AolAware                                          INTEGER,
        	gtmAttr2CheckStaticDepends                                INTEGER,
        	gtmAttr2CheckDynamicDepends                               INTEGER,
        	gtmAttr2DrainRequests                                     INTEGER,
        	gtmAttr2EnableResetsRipeness                              INTEGER,
        	gtmAttr2FbRespectDepends                                  INTEGER,
        	gtmAttr2FbRespectAcl                                      INTEGER,
        	gtmAttr2DefaultAlternate                                  INTEGER,
        	gtmAttr2DefaultFallback                                   INTEGER,
        	gtmAttr2PersistMask                                       Gauge,
        	gtmAttr2GtmSetsRecursion                                  INTEGER,
        	gtmAttr2QosFactorLcs                                      Gauge,
        	gtmAttr2QosFactorRtt                                      Gauge,
        	gtmAttr2QosFactorHops                                     Gauge,
        	gtmAttr2QosFactorHitRatio                                 Gauge,
        	gtmAttr2QosFactorPacketRate                               Gauge,
        	gtmAttr2QosFactorBps                                      Gauge,
        	gtmAttr2QosFactorVsCapacity                               Gauge,
        	gtmAttr2QosFactorTopology                                 Gauge,
        	gtmAttr2QosFactorConnRate                                 Gauge,
        	gtmAttr2TimerRetryPathData                                Gauge,
        	gtmAttr2TimerGetAutoconfigData                            Gauge,
        	gtmAttr2TimerPersistCache                                 Gauge,
        	gtmAttr2DefaultProbeLimit                                 Gauge,
        	gtmAttr2DownThreshold                                     Gauge,
        	gtmAttr2DownMultiple                                      Gauge,
        	gtmAttr2PathTtl                                           Gauge,
        	gtmAttr2TraceTtl                                          Gauge,
        	gtmAttr2LdnsDuration                                      Gauge,
        	gtmAttr2PathDuration                                      Gauge,
        	gtmAttr2RttSampleCount                                    Gauge,
        	gtmAttr2RttPacketLength                                   Gauge,
        	gtmAttr2RttTimeout                                        Gauge,
        	gtmAttr2MaxMonReqs                                        Gauge,
        	gtmAttr2TraceroutePort                                    Gauge,
        	gtmAttr2PathsNeverDie                                     INTEGER,
        	gtmAttr2ProbeDisabledObjects                              INTEGER,
        	gtmAttr2LinkLimitFactor                                   Gauge,
        	gtmAttr2OverLimitLinkLimitFactor                          Gauge,
        	gtmAttr2LinkPrepaidFactor                                 Gauge,
        	gtmAttr2LinkCompensateInbound                             Gauge,
        	gtmAttr2LinkCompensateOutbound                            Gauge,
        	gtmAttr2LinkCompensationHistory                           Gauge,
        	gtmAttr2MaxLinkOverLimitCount                             Gauge,
        	gtmAttr2LowerBoundPctRow                                  Gauge,
        	gtmAttr2LowerBoundPctCol                                  Gauge,
        	gtmAttr2Autoconf                                          INTEGER,
        	gtmAttr2Autosync                                          INTEGER,
        	gtmAttr2SyncNamedConf                                     INTEGER,
        	gtmAttr2SyncGroup                                         LongDisplayString,
        	gtmAttr2SyncTimeout                                       Gauge,
        	gtmAttr2SyncZonesTimeout                                  Gauge,
        	gtmAttr2TimeTolerance                                     Gauge,
        	gtmAttr2TopologyLongestMatch                              INTEGER,
        	gtmAttr2TopologyAclThreshold                              Gauge,
        	gtmAttr2StaticPersistCidr                                 Gauge,
        	gtmAttr2StaticPersistV6Cidr                               Gauge,
        	gtmAttr2QosFactorVsScore                                  Gauge,
        	gtmAttr2TimerSendKeepAlive                                Gauge,
        	gtmAttr2CertificateDepth                                  Gauge,
        	gtmAttr2MaxMemoryUsage                                    Gauge,
        	gtmAttr2Name                                              LongDisplayString,
        	gtmAttr2ForwardStatus                                     INTEGER
	}

gtmAttr2DumpTopology OBJECT-TYPE
	SYNTAX INTEGER {
		false(0),
		true(1)
	}
	MAX-ACCESS read-only
	STATUS current
	DESCRIPTION
		"The state indicating whether or not to dump the topology."
	::= { gtmAttr2Entry 1 }

gtmAttr2CacheLdns OBJECT-TYPE
	SYNTAX INTEGER {
		false(0),
		true(1)
	}
	MAX-ACCESS read-only
	STATUS current
	DESCRIPTION
		"The state indicating whether or not to cache LDNSes."
	::= { gtmAttr2Entry 2 }

gtmAttr2AolAware OBJECT-TYPE
	SYNTAX INTEGER {
		false(0),
		true(1)
	}
	MAX-ACCESS read-only
	STATUS current
	DESCRIPTION
		"The state indicating whether or not local DNS servers that
		belong to AOL (America Online) are recognized."
	::= { gtmAttr2Entry 3 }

gtmAttr2CheckStaticDepends OBJECT-TYPE
	SYNTAX INTEGER {
		false(0),
		true(1)
	}
	MAX-ACCESS read-only
	STATUS current
	DESCRIPTION
		"The state indicating whether or not to check the availability
		of virtual servers."
	::= { gtmAttr2Entry 4 }

gtmAttr2CheckDynamicDepends OBJECT-TYPE
	SYNTAX INTEGER {
		false(0),
		true(1)
	}
	MAX-ACCESS read-only
	STATUS current
	DESCRIPTION
		"The state indicating whether or not to check availability of
		a path before it uses the path for load balancing."
	::= { gtmAttr2Entry 5 }

gtmAttr2DrainRequests OBJECT-TYPE
	SYNTAX INTEGER {
		false(0),
		true(1)
	}
	MAX-ACCESS read-only
	STATUS current
	DESCRIPTION
		"The state indicating whether or not persistent connections
		are allowed to remain connected, until TTL expires,
		when disabling a pool."
	::= { gtmAttr2Entry 6 }

gtmAttr2EnableResetsRipeness OBJECT-TYPE
	SYNTAX INTEGER {
		false(0),
		true(1)
	}
	MAX-ACCESS read-only
	STATUS current
	DESCRIPTION
		"The state indicating whether or not ripeness value is allowed
		to be reset."
	::= { gtmAttr2Entry 7 }

gtmAttr2FbRespectDepends OBJECT-TYPE
	SYNTAX INTEGER {
		false(0),
		true(1)
	}
	MAX-ACCESS read-only
	STATUS current
	DESCRIPTION
		"The state indicating whether or not to respect virtual server
		status when load balancing switches to the fallback mode."
	::= { gtmAttr2Entry 8 }

gtmAttr2FbRespectAcl OBJECT-TYPE
	SYNTAX INTEGER {
		false(0),
		true(1)
	}
	MAX-ACCESS read-only
	STATUS	 deprecated
	DESCRIPTION
		"Deprecated! The state indicating whether or not to respect ACL.
	         This is part of an outdated mechanism for disabling virtual servers"
	::= { gtmAttr2Entry 9 }

gtmAttr2DefaultAlternate OBJECT-TYPE
	SYNTAX INTEGER {
		returntodns(0),
		null(1),
		roundrobin(2),
		ratio(3),
		topology(4),
		statpersist(5),
		ga(6),
		vscapacity(7),
		leastconn(8),
		lowestrtt(9),
		lowesthops(10),
		packetrate(11),
		cpu(12),
		hitratio(13),
		qos(14),
		bps(15),
		droppacket(16),
		explicitip(17),
		vssore(18)
	}
	MAX-ACCESS read-only
	STATUS current
	DESCRIPTION
		"The default alternate LB method."
	::= { gtmAttr2Entry 10 }

gtmAttr2DefaultFallback OBJECT-TYPE
	SYNTAX INTEGER {
		returntodns(0),
		null(1),
		roundrobin(2),
		ratio(3),
		topology(4),
		statpersit(5),
		ga(6),
		vscapacity(7),
		leastconn(8),
		lowestrtt(9),
		lowesthops(10),
		packetrate(11),
		cpu(12),
		hitratio(13),
		qos(14),
		bps(15),
		droppacket(16),
		explicitip(17),
		vsscore(18)
	}
	MAX-ACCESS read-only
	STATUS current
	DESCRIPTION
		"The default fallback LB method."
	::= { gtmAttr2Entry 11 }

gtmAttr2PersistMask OBJECT-TYPE
	SYNTAX Gauge
	MAX-ACCESS read-only
	STATUS	 deprecated
	DESCRIPTION
		"Deprecated! Replaced by gtmAttrStaticPersistCidr and gtmAttrStaticPersistV6Cidr.
		The persistence mask which is used to determine the netmask applied
		for static persistance requests."
	::= { gtmAttr2Entry 12 }

gtmAttr2GtmSetsRecursion OBJECT-TYPE
	SYNTAX INTEGER {
		false(0),
		true(1)
	}
	MAX-ACCESS read-only
	STATUS current
	DESCRIPTION
		"The state indicating whether set recursion by global
		traffic management object(GTM) is enable or not."
	::= { gtmAttr2Entry 13 }

gtmAttr2QosFactorLcs OBJECT-TYPE
	SYNTAX Gauge
	MAX-ACCESS read-only
	STATUS current
	DESCRIPTION
		"The factor used to normalize link capacity values
		when the load balancing mode is set to LB_METHOD_QOS."
	::= { gtmAttr2Entry 14 }

gtmAttr2QosFactorRtt OBJECT-TYPE
	SYNTAX Gauge
	MAX-ACCESS read-only
	STATUS current
	DESCRIPTION
		"The factor used to normalize round-trip time values
		when the load balancing mode is set to LB_METHOD_QOS."
	::= { gtmAttr2Entry 15 }

gtmAttr2QosFactorHops OBJECT-TYPE
	SYNTAX Gauge
	MAX-ACCESS read-only
	STATUS current
	DESCRIPTION
		"The factor used to normalize hops when the load
		balancing mode is set to LB_METHOD_QOS."
	::= { gtmAttr2Entry 16 }

gtmAttr2QosFactorHitRatio OBJECT-TYPE
	SYNTAX Gauge
	MAX-ACCESS read-only
	STATUS current
	DESCRIPTION
		"The factor used to normalize ping packet completion
		rates when the load balancing mode is set to LB_METHOD_QOS."
	::= { gtmAttr2Entry 17 }

gtmAttr2QosFactorPacketRate OBJECT-TYPE
	SYNTAX Gauge
	MAX-ACCESS read-only
	STATUS current
	DESCRIPTION
		"The factor used to normalize packet rates when the load
		balancing mode is set to LB_METHOD_QOS."
	::= { gtmAttr2Entry 18 }

gtmAttr2QosFactorBps OBJECT-TYPE
	SYNTAX Gauge
	MAX-ACCESS read-only
	STATUS current
	DESCRIPTION
		"The factor used to normalize kilobytes per second
		when the load balancing mode is set to LB_METHOD_QOS."
	::= { gtmAttr2Entry 19 }

gtmAttr2QosFactorVsCapacity OBJECT-TYPE
	SYNTAX Gauge
	MAX-ACCESS read-only
	STATUS current
	DESCRIPTION
		"The factor used to normalize virtual server capacity
		values when the load balancing mode is set to LB_METHOD_QOS."
	::= { gtmAttr2Entry 20 }

gtmAttr2QosFactorTopology OBJECT-TYPE
	SYNTAX Gauge
	MAX-ACCESS read-only
	STATUS current
	DESCRIPTION
		"The factor used to normalize topology values when the load
		balancing mode is set to LB_METHOD_QOS."
	::= { gtmAttr2Entry 21 }

gtmAttr2QosFactorConnRate OBJECT-TYPE
	SYNTAX Gauge
	MAX-ACCESS read-only
	STATUS	 deprecated
	DESCRIPTION
		"Deprecated!
		Replaced by gtmAttrQosFactorVsScore.
		The factor used to normalize connection rates when the load
		balancing mode is set to LB_METHOD_QOS."
	::= { gtmAttr2Entry 22 }

gtmAttr2TimerRetryPathData OBJECT-TYPE
	SYNTAX Gauge
	MAX-ACCESS read-only
	STATUS current
	DESCRIPTION
		"The frequency at which to retrieve path data."
	::= { gtmAttr2Entry 23 }

gtmAttr2TimerGetAutoconfigData OBJECT-TYPE
	SYNTAX Gauge
	MAX-ACCESS read-only
	STATUS current
	DESCRIPTION
		"The frequency at which to retrieve auto-configuration data."
	::= { gtmAttr2Entry 24 }

gtmAttr2TimerPersistCache OBJECT-TYPE
	SYNTAX Gauge
	MAX-ACCESS read-only
	STATUS current
	DESCRIPTION
		"The frequency at which to retrieve path and metrics
		data from the system cache."
	::= { gtmAttr2Entry 25 }

gtmAttr2DefaultProbeLimit OBJECT-TYPE
	SYNTAX Gauge
	MAX-ACCESS read-only
	STATUS current
	DESCRIPTION
		"The default probe limit, the number of times to probe a path."
	::= { gtmAttr2Entry 26 }

gtmAttr2DownThreshold OBJECT-TYPE
	SYNTAX Gauge
	MAX-ACCESS read-only
	STATUS current
	DESCRIPTION
		"The down_threshold value. If a host server or a host virtual server
		has been marked down for the last down_threshold probing cycles
		(timer_get_host_data or timer_get_vs_data respectively), then perform
		service checks every down_multiple * timer period instead."
	::= { gtmAttr2Entry 27 }

gtmAttr2DownMultiple OBJECT-TYPE
	SYNTAX Gauge
	MAX-ACCESS read-only
	STATUS current
	DESCRIPTION
		"The down_multiple value. If a host server or a host virtual server
		has been marked down for the last down_threshold probing cycles
		(timer_get_host_data or timer_get_vs_data respectively), then perform
		service checks every down_multiple * timer period instead."
	::= { gtmAttr2Entry 28 }

gtmAttr2PathTtl OBJECT-TYPE
	SYNTAX Gauge
	MAX-ACCESS read-only
	STATUS current
	DESCRIPTION
		"The TTL for the path information."
	::= { gtmAttr2Entry 29 }

gtmAttr2TraceTtl OBJECT-TYPE
	SYNTAX Gauge
	MAX-ACCESS read-only
	STATUS current
	DESCRIPTION
		"The TTL for the traceroute information."
	::= { gtmAttr2Entry 30 }

gtmAttr2LdnsDuration OBJECT-TYPE
	SYNTAX Gauge
	MAX-ACCESS read-only
	STATUS current
	DESCRIPTION
		"The number of seconds that an inactive LDNS remains cached."
	::= { gtmAttr2Entry 31 }

gtmAttr2PathDuration OBJECT-TYPE
	SYNTAX Gauge
	MAX-ACCESS read-only
	STATUS current
	DESCRIPTION
		"The number of seconds that a path remains cached after its last access."
	::= { gtmAttr2Entry 32 }

gtmAttr2RttSampleCount OBJECT-TYPE
	SYNTAX Gauge
	MAX-ACCESS read-only
	STATUS current
	DESCRIPTION
		"The number of packets to send out in a probe request to determine
		path information."
	::= { gtmAttr2Entry 33 }

gtmAttr2RttPacketLength OBJECT-TYPE
	SYNTAX Gauge
	MAX-ACCESS read-only
	STATUS current
	DESCRIPTION
		"The length of the packet sent out in a probe request to determine
		path information."
	::= { gtmAttr2Entry 34 }

gtmAttr2RttTimeout OBJECT-TYPE
	SYNTAX Gauge
	MAX-ACCESS read-only
	STATUS current
	DESCRIPTION
		"The timeout for RTT, in seconds."
	::= { gtmAttr2Entry 35 }

gtmAttr2MaxMonReqs OBJECT-TYPE
	SYNTAX Gauge
	MAX-ACCESS read-only
	STATUS current
	DESCRIPTION
		"The maximum synchronous monitor request, which is used to control
		the maximum number of monitor requests being sent out at one time
		for a given probing interval. This will allow the user to smooth out
		monitor probe requests as much as they desire."
	::= { gtmAttr2Entry 36 }

gtmAttr2TraceroutePort OBJECT-TYPE
	SYNTAX Gauge
	MAX-ACCESS read-only
	STATUS current
	DESCRIPTION
		"The port to use to collect traceroute (hops) data."
	::= { gtmAttr2Entry 37 }

gtmAttr2PathsNeverDie OBJECT-TYPE
	SYNTAX INTEGER {
		false(0),
		true(1)
	}
	MAX-ACCESS read-only
	STATUS current
	DESCRIPTION
		"The state indicating whether the dynamic load balancing modes
		can use path data even after the TTL for the path data has expired."
	::= { gtmAttr2Entry 38 }

gtmAttr2ProbeDisabledObjects OBJECT-TYPE
	SYNTAX INTEGER {
		false(0),
		true(1)
	}
	MAX-ACCESS read-only
	STATUS current
	DESCRIPTION
		"The state indicating whether probing disabled objects by global
		traffic management object(GTM) is enabled or not."
	::= { gtmAttr2Entry 39 }

gtmAttr2LinkLimitFactor OBJECT-TYPE
	SYNTAX Gauge
	MAX-ACCESS read-only
	STATUS current
	DESCRIPTION
		"The link limit factor, which is used to set a target percentage
		for traffic. For example, if it is set to 90, the ratio cost
		based load-balancing will set a ratio with a maximum value equal
		to 90% of the limit value for the link. Default is 95%."
	::= { gtmAttr2Entry 40 }

gtmAttr2OverLimitLinkLimitFactor OBJECT-TYPE
	SYNTAX Gauge
	MAX-ACCESS read-only
	STATUS current
	DESCRIPTION
		"The over-limit link limit factor. If traffic on a link exceeds
		the limit, this factor will be used instead of the link_limit_factor
		until the traffic is over limit for more than max_link_over_limit_count
		times. Once the limit has been exceeded too many times, all traffic
		is shut off for the link. The default for
		over_limit_link_limit_factor is 90%."
	::= { gtmAttr2Entry 41 }

gtmAttr2LinkPrepaidFactor OBJECT-TYPE
	SYNTAX Gauge
	MAX-ACCESS read-only
	STATUS current
	DESCRIPTION
		"The link prepaid factor. Maximum percentage of traffic allocated
		to link which has a traffic allotment which has been prepaid.
		Default is 95%."
	::= { gtmAttr2Entry 42 }

gtmAttr2LinkCompensateInbound OBJECT-TYPE
	SYNTAX Gauge
	MAX-ACCESS read-only
	STATUS current
	DESCRIPTION
		"The link compensate inbound. If set, the link allotment calculation
		will take into account traffic which does not flow through the BIGIP,
		i.e. if more traffic is flowing through a link as measured by SNMP
		on the router than is flowing through the BIGIP. This applies to
		inbound traffic which the major volume will initiate from internal
		clients."
	::= { gtmAttr2Entry 43 }

gtmAttr2LinkCompensateOutbound OBJECT-TYPE
	SYNTAX Gauge
	MAX-ACCESS read-only
	STATUS current
	DESCRIPTION
		"The link compensate outbound. If set, the link allotment calculation
		will take into account traffic which does not flow through the BIGIP,
		i.e. if more traffic is flowing through a link as measured by SNMP
		on the router than is flowing through the BIGIP. This applies to
		outbound traffic which the major volume will initiate from internal
		clients."
	::= { gtmAttr2Entry 44 }

gtmAttr2LinkCompensationHistory OBJECT-TYPE
	SYNTAX Gauge
	MAX-ACCESS read-only
	STATUS current
	DESCRIPTION
		"The link compensation history."
	::= { gtmAttr2Entry 45 }

gtmAttr2MaxLinkOverLimitCount OBJECT-TYPE
	SYNTAX Gauge
	MAX-ACCESS read-only
	STATUS current
	DESCRIPTION
		"The maximum link over limit count. The count of how many times
		in a row traffic may be over the defined limit for the link before
		it is shut off entirely. Default is 1."
	::= { gtmAttr2Entry 46 }

gtmAttr2LowerBoundPctRow OBJECT-TYPE
	SYNTAX Gauge
	MAX-ACCESS read-only
	STATUS	 deprecated
	DESCRIPTION
		"Deprecated! No longer useful.
	        The lower bound percentage row option in Internet Weather Map."
	::= { gtmAttr2Entry 47 }

gtmAttr2LowerBoundPctCol OBJECT-TYPE
	SYNTAX Gauge
	MAX-ACCESS read-only
	STATUS	 deprecated
	DESCRIPTION
		"Deprecated! No longer useful.
	        The lower bound percentage column option in Internet Weather Map."
	::= { gtmAttr2Entry 48 }

gtmAttr2Autoconf OBJECT-TYPE
	SYNTAX INTEGER {
		false(0),
		true(1)
	}
	MAX-ACCESS read-only
	STATUS current
	DESCRIPTION
		"The state indicating whether to auto configure BIGIP/3DNS servers
		(automatic addition and deletion of self IPs and virtual servers)."
	::= { gtmAttr2Entry 49 }

gtmAttr2Autosync OBJECT-TYPE
	SYNTAX INTEGER {
		false(0),
		true(1)
	}
	MAX-ACCESS read-only
	STATUS current
	DESCRIPTION
		"The state indicating whether or not to autosync.
		Allows automatic updates of wideip.conf to/from other 3-DNSes."
	::= { gtmAttr2Entry 50 }

gtmAttr2SyncNamedConf OBJECT-TYPE
	SYNTAX INTEGER {
		false(0),
		true(1)
	}
	MAX-ACCESS read-only
	STATUS current
	DESCRIPTION
		"The state indicating whether or not to auto-synchronize named
		configuration. Allows automatic updates of named.conf to/from other 3-DNSes."
	::= { gtmAttr2Entry 51 }

gtmAttr2SyncGroup OBJECT-TYPE
	SYNTAX LongDisplayString
	MAX-ACCESS read-only
	STATUS current
	DESCRIPTION
		"The name of sync group."
	::= { gtmAttr2Entry 52 }

gtmAttr2SyncTimeout OBJECT-TYPE
	SYNTAX Gauge
	MAX-ACCESS read-only
	STATUS current
	DESCRIPTION
		"The sync timeout.  If synch'ing from a remote 3-DNS takes longer than
		this timeout, then abort the connection."
	::= { gtmAttr2Entry 53 }

gtmAttr2SyncZonesTimeout OBJECT-TYPE
	SYNTAX Gauge
	MAX-ACCESS read-only
	STATUS current
	DESCRIPTION
		"The sync zones timeout. If synch'ing named and zone configuration
		takes this timeout, then abort the connection."
	::= { gtmAttr2Entry 54 }

gtmAttr2TimeTolerance OBJECT-TYPE
	SYNTAX Gauge
	MAX-ACCESS read-only
	STATUS current
	DESCRIPTION
		"The allowable time difference for data to be out of sync between
		members of a sync group."
	::= { gtmAttr2Entry 55 }

gtmAttr2TopologyLongestMatch OBJECT-TYPE
	SYNTAX INTEGER {
		false(0),
		true(1)
	}
	MAX-ACCESS read-only
	STATUS current
	DESCRIPTION
		"The state indicating  whether or not the 3-DNS Controller selects
		the topology record that is most specific and, thus, has the longest
		match, in cases where there are several IP/netmask items that match
		a particular IP address.
		If it is set to false, the 3-DNS Controller uses the first topology record
		that matches (according to the order of entry) in the topology statement."
	::= { gtmAttr2Entry 56 }

gtmAttr2TopologyAclThreshold OBJECT-TYPE
	SYNTAX Gauge
	MAX-ACCESS read-only
	STATUS	 deprecated
	DESCRIPTION
		"Deprecated! The threshold of the topology ACL.
	         This is an outdated mechanism for disabling a node."
	::= { gtmAttr2Entry 57 }

gtmAttr2StaticPersistCidr OBJECT-TYPE
	SYNTAX Gauge
	MAX-ACCESS read-only
	STATUS current
	DESCRIPTION
		"The variable used with the static persistence load balancing mode
		to allow users to specify what cidr should be used.
		This is used for IPv4."
	::= { gtmAttr2Entry 58 }

gtmAttr2StaticPersistV6Cidr OBJECT-TYPE
	SYNTAX Gauge
	MAX-ACCESS read-only
	STATUS current
	DESCRIPTION
		"The variable used with the static persistence load balancing mode
		to allow users to specify what cidr should be used.
		This is used for IPv6."
	::= { gtmAttr2Entry 59 }

gtmAttr2QosFactorVsScore OBJECT-TYPE
	SYNTAX Gauge
	MAX-ACCESS read-only
	STATUS current
	DESCRIPTION
		"The factor used to normalize virtual server (VS) score
		when the load balancing mode is set to LB_METHOD_QOS."
	::= { gtmAttr2Entry 60 }

gtmAttr2TimerSendKeepAlive OBJECT-TYPE
	SYNTAX Gauge
	MAX-ACCESS read-only
	STATUS current
	DESCRIPTION
		"The frequency of GTM keep alive messages (strictly the config timestamps)."
	::= { gtmAttr2Entry 61 }

gtmAttr2CertificateDepth OBJECT-TYPE
	SYNTAX Gauge
	MAX-ACCESS read-only
	STATUS	 deprecated
	DESCRIPTION
		"Deprecated! No longer updated.
	        When non-zero, customers may use their own SSL certificates by setting the certificate depth."
	::= { gtmAttr2Entry 62 }

gtmAttr2MaxMemoryUsage OBJECT-TYPE
	SYNTAX Gauge
	MAX-ACCESS read-only
	STATUS	 deprecated
	DESCRIPTION
		"Deprecated! The maximum amount of memory (in MB) allocated to GTM."
	::= { gtmAttr2Entry 63 }

gtmAttr2Name OBJECT-TYPE
	SYNTAX LongDisplayString
	MAX-ACCESS read-only
	STATUS current
	DESCRIPTION
		"name as a key."
	::= { gtmAttr2Entry 64 }

gtmAttr2ForwardStatus OBJECT-TYPE
	SYNTAX INTEGER {
		disabled(0),
		enabled(1)
	}
	MAX-ACCESS read-only
	STATUS current
	DESCRIPTION
		"The state indicating whether or not to forward object availability status change notifications."
	::= { gtmAttr2Entry 65 }

--==================================================================
-- Gtm_dnssec_zone_stat
--==================================================================
gtmDnssecZoneStatResetStats OBJECT-TYPE
	SYNTAX INTEGER
	MAX-ACCESS read-write
	STATUS current
	DESCRIPTION
		"The action to reset resettable statistics data in gtmDnssecZoneStat.
		 Setting this value to 1 will reset statistics data.
		 Note, some statistics data may not be reset including data that are incremental counters."
	::= { gtmDnssecZoneStat 1 }

gtmDnssecZoneStatNumber OBJECT-TYPE
	SYNTAX INTEGER
	MAX-ACCESS read-only
	STATUS current
	DESCRIPTION
		"The number of gtmDnssecZoneStat entries in the table."
	::= { gtmDnssecZoneStat 2 }

gtmDnssecZoneStatTable OBJECT-TYPE
	SYNTAX SEQUENCE OF GtmDnssecZoneStatEntry
	MAX-ACCESS not-accessible
	STATUS current
	DESCRIPTION
		"A table containing statistics information for GTM DNSSEC zones."
	::= { gtmDnssecZoneStat 3 }

gtmDnssecZoneStatEntry OBJECT-TYPE
	SYNTAX  GtmDnssecZoneStatEntry
	MAX-ACCESS not-accessible
	STATUS current
	DESCRIPTION
		"Columns in the gtmDnssecZoneStat Table"
	INDEX {
		gtmDnssecZoneStatName
	}
	::= { gtmDnssecZoneStatTable 1 }

GtmDnssecZoneStatEntry ::=
	SEQUENCE {
        	gtmDnssecZoneStatName                                     LongDisplayString,
        	gtmDnssecZoneStatNsec3s                                   Counter64,
        	gtmDnssecZoneStatNsec3Nodata                              Counter64,
        	gtmDnssecZoneStatNsec3Nxdomain                            Counter64,
        	gtmDnssecZoneStatNsec3Referral                            Counter64,
        	gtmDnssecZoneStatNsec3Resalt                              Counter64,
        	gtmDnssecZoneStatDnssecResponses                          Counter64,
        	gtmDnssecZoneStatDnssecDnskeyQueries                      Counter64,
        	gtmDnssecZoneStatDnssecNsec3paramQueries                  Counter64,
        	gtmDnssecZoneStatDnssecDsQueries                          Counter64,
        	gtmDnssecZoneStatSigCryptoFailed                          Counter64,
        	gtmDnssecZoneStatSigSuccess                               Counter64,
        	gtmDnssecZoneStatSigFailed                                Counter64,
        	gtmDnssecZoneStatSigRrsetFailed                           Counter64,
        	gtmDnssecZoneStatConnectFlowFailed                        Counter64,
        	gtmDnssecZoneStatTowireFailed                             Counter64,
        	gtmDnssecZoneStatAxfrQueries                              Counter64,
        	gtmDnssecZoneStatIxfrQueries                              Counter64,
        	gtmDnssecZoneStatXfrStarts                                Counter64,
        	gtmDnssecZoneStatXfrCompletes                             Counter64,
        	gtmDnssecZoneStatXfrMsgs                                  Counter64,
        	gtmDnssecZoneStatXfrMasterMsgs                            Counter64,
        	gtmDnssecZoneStatXfrResponseAverageSize                   Counter64,
        	gtmDnssecZoneStatXfrSerial                                Counter64,
        	gtmDnssecZoneStatXfrMasterSerial                          Counter64,
        	gtmDnssecZoneStatDsXfr                                    Counter64,
        	gtmDnssecZoneStatDsReferral                               Counter64,
        	gtmDnssecZoneStatDnssecCdsQueries                         Counter64,
        	gtmDnssecZoneStatDnssecCdnskeyQueries                     Counter64
	}

gtmDnssecZoneStatName OBJECT-TYPE
	SYNTAX LongDisplayString
	MAX-ACCESS read-only
	STATUS current
	DESCRIPTION
		"The name of a DNSSEC zone."
	::= { gtmDnssecZoneStatEntry 1 }

gtmDnssecZoneStatNsec3s OBJECT-TYPE
	SYNTAX Counter64
	MAX-ACCESS read-only
	STATUS current
	DESCRIPTION
		"Total number of NSEC3 RRs generated."
	::= { gtmDnssecZoneStatEntry 2 }

gtmDnssecZoneStatNsec3Nodata OBJECT-TYPE
	SYNTAX Counter64
	MAX-ACCESS read-only
	STATUS current
	DESCRIPTION
		"Total number of no data responses generated needing NSEC3 RR."
	::= { gtmDnssecZoneStatEntry 3 }

gtmDnssecZoneStatNsec3Nxdomain OBJECT-TYPE
	SYNTAX Counter64
	MAX-ACCESS read-only
	STATUS current
	DESCRIPTION
		"Total number of no domain responses generated needing NSEC3 RR."
	::= { gtmDnssecZoneStatEntry 4 }

gtmDnssecZoneStatNsec3Referral OBJECT-TYPE
	SYNTAX Counter64
	MAX-ACCESS read-only
	STATUS current
	DESCRIPTION
		"Total number of referral responses generated needing NSEC3 RR."
	::= { gtmDnssecZoneStatEntry 5 }

gtmDnssecZoneStatNsec3Resalt OBJECT-TYPE
	SYNTAX Counter64
	MAX-ACCESS read-only
	STATUS current
	DESCRIPTION
		"Total number of times that salt was changed for NSEC3."
	::= { gtmDnssecZoneStatEntry 6 }

gtmDnssecZoneStatDnssecResponses OBJECT-TYPE
	SYNTAX Counter64
	MAX-ACCESS read-only
	STATUS current
	DESCRIPTION
		"Total number of signed responses."
	::= { gtmDnssecZoneStatEntry 7 }

gtmDnssecZoneStatDnssecDnskeyQueries OBJECT-TYPE
	SYNTAX Counter64
	MAX-ACCESS read-only
	STATUS current
	DESCRIPTION
		"Total number of queries for DNSKEY type."
	::= { gtmDnssecZoneStatEntry 8 }

gtmDnssecZoneStatDnssecNsec3paramQueries OBJECT-TYPE
	SYNTAX Counter64
	MAX-ACCESS read-only
	STATUS current
	DESCRIPTION
		"Total number of queries for NSEC3PARAM type."
	::= { gtmDnssecZoneStatEntry 9 }

gtmDnssecZoneStatDnssecDsQueries OBJECT-TYPE
	SYNTAX Counter64
	MAX-ACCESS read-only
	STATUS current
	DESCRIPTION
		"Total number of queries for DS type."
	::= { gtmDnssecZoneStatEntry 10 }

gtmDnssecZoneStatSigCryptoFailed OBJECT-TYPE
	SYNTAX Counter64
	MAX-ACCESS read-only
	STATUS current
	DESCRIPTION
		"Total number of signatures in which the cryptographic operation failed."
	::= { gtmDnssecZoneStatEntry 11 }

gtmDnssecZoneStatSigSuccess OBJECT-TYPE
	SYNTAX Counter64
	MAX-ACCESS read-only
	STATUS current
	DESCRIPTION
		"Total number of successfully generated signatures."
	::= { gtmDnssecZoneStatEntry 12 }

gtmDnssecZoneStatSigFailed OBJECT-TYPE
	SYNTAX Counter64
	MAX-ACCESS read-only
	STATUS current
	DESCRIPTION
		"Total number of general signature failures."
	::= { gtmDnssecZoneStatEntry 13 }

gtmDnssecZoneStatSigRrsetFailed OBJECT-TYPE
	SYNTAX Counter64
	MAX-ACCESS read-only
	STATUS current
	DESCRIPTION
		"Total number of failures due to an RRSET failing to be signed."
	::= { gtmDnssecZoneStatEntry 14 }

gtmDnssecZoneStatConnectFlowFailed OBJECT-TYPE
	SYNTAX Counter64
	MAX-ACCESS read-only
	STATUS current
	DESCRIPTION
		"Total number of connection flow failures."
	::= { gtmDnssecZoneStatEntry 15 }

gtmDnssecZoneStatTowireFailed OBJECT-TYPE
	SYNTAX Counter64
	MAX-ACCESS read-only
	STATUS current
	DESCRIPTION
		"Total number of failures when converting to a wire format packet."
	::= { gtmDnssecZoneStatEntry 16 }

gtmDnssecZoneStatAxfrQueries OBJECT-TYPE
	SYNTAX Counter64
	MAX-ACCESS read-only
	STATUS current
	DESCRIPTION
		"Total number of axfr queries."
	::= { gtmDnssecZoneStatEntry 17 }

gtmDnssecZoneStatIxfrQueries OBJECT-TYPE
	SYNTAX Counter64
	MAX-ACCESS read-only
	STATUS current
	DESCRIPTION
		"Total number of ixfr queries."
	::= { gtmDnssecZoneStatEntry 18 }

gtmDnssecZoneStatXfrStarts OBJECT-TYPE
	SYNTAX Counter64
	MAX-ACCESS read-only
	STATUS current
	DESCRIPTION
		"Total number of zone transfers which were started."
	::= { gtmDnssecZoneStatEntry 19 }

gtmDnssecZoneStatXfrCompletes OBJECT-TYPE
	SYNTAX Counter64
	MAX-ACCESS read-only
	STATUS current
	DESCRIPTION
		"Total number of zone transfers which were completed."
	::= { gtmDnssecZoneStatEntry 20 }

gtmDnssecZoneStatXfrMsgs OBJECT-TYPE
	SYNTAX Counter64
	MAX-ACCESS read-only
	STATUS current
	DESCRIPTION
		"Total number of zone transfer packets to clients."
	::= { gtmDnssecZoneStatEntry 21 }

gtmDnssecZoneStatXfrMasterMsgs OBJECT-TYPE
	SYNTAX Counter64
	MAX-ACCESS read-only
	STATUS current
	DESCRIPTION
		"Total number of zone transfer packets from the primary server."
	::= { gtmDnssecZoneStatEntry 22 }

gtmDnssecZoneStatXfrResponseAverageSize OBJECT-TYPE
	SYNTAX Counter64
	MAX-ACCESS read-only
	STATUS current
	DESCRIPTION
		"Zone transfer average responses size in bytes."
	::= { gtmDnssecZoneStatEntry 23 }

gtmDnssecZoneStatXfrSerial OBJECT-TYPE
	SYNTAX Counter64
	MAX-ACCESS read-only
	STATUS current
	DESCRIPTION
		"The serial number advertised to all clients."
	::= { gtmDnssecZoneStatEntry 24 }

gtmDnssecZoneStatXfrMasterSerial OBJECT-TYPE
	SYNTAX Counter64
	MAX-ACCESS read-only
	STATUS current
	DESCRIPTION
		"The zone serial number of the primary server."
	::= { gtmDnssecZoneStatEntry 25 }

gtmDnssecZoneStatDsXfr OBJECT-TYPE
	SYNTAX Counter64
	MAX-ACCESS read-only
	STATUS current
	DESCRIPTION
		"Total number of DS record sets that were added to BIG-IP DNSSEC enabled zone transfers."
	::= { gtmDnssecZoneStatEntry 26 }

gtmDnssecZoneStatDsReferral OBJECT-TYPE
	SYNTAX Counter64
	MAX-ACCESS read-only
	STATUS current
	DESCRIPTION
		"Total number of referral responses generated in which DS RR(s) were added."
	::= { gtmDnssecZoneStatEntry 27 }

gtmDnssecZoneStatDnssecCdsQueries OBJECT-TYPE
	SYNTAX Counter64
	MAX-ACCESS read-only
	STATUS current
	DESCRIPTION
		"Total number of queries for CDS type."
	::= { gtmDnssecZoneStatEntry 28 }

gtmDnssecZoneStatDnssecCdnskeyQueries OBJECT-TYPE
	SYNTAX Counter64
	MAX-ACCESS read-only
	STATUS current
	DESCRIPTION
		"Total number of queries for CDNSKEY type."
	::= { gtmDnssecZoneStatEntry 29 }

--==================================================================
-- Global_gtm_dnssec_zone_stat
--==================================================================
gtmDnssecStatResetStats OBJECT-TYPE
	SYNTAX INTEGER
	MAX-ACCESS read-write
	STATUS current
	DESCRIPTION
		"The action to reset resettable statistics data in gtmGlobalDnssecStat.
		 Setting this value to 1 will reset statistics data.
		 Note, some statistics data may not be reset including data that are incremental counters."
	::= { gtmGlobalDnssecStat 1 }

gtmDnssecStatNsec3s OBJECT-TYPE
	SYNTAX Counter64
	MAX-ACCESS read-only
	STATUS current
	DESCRIPTION
		"The number of NSEC3 RRs generated."
	::= { gtmGlobalDnssecStat 2 }

gtmDnssecStatNsec3Nodata OBJECT-TYPE
	SYNTAX Counter64
	MAX-ACCESS read-only
	STATUS current
	DESCRIPTION
		"The number of no data responses generated needing NSEC3 RR."
	::= { gtmGlobalDnssecStat 3 }

gtmDnssecStatNsec3Nxdomain OBJECT-TYPE
	SYNTAX Counter64
	MAX-ACCESS read-only
	STATUS current
	DESCRIPTION
		"The number of no domain responses generated needing NSEC3 RR."
	::= { gtmGlobalDnssecStat 4 }

gtmDnssecStatNsec3Referral OBJECT-TYPE
	SYNTAX Counter64
	MAX-ACCESS read-only
	STATUS current
	DESCRIPTION
		"The number of referral responses generated needing NSEC3 RR."
	::= { gtmGlobalDnssecStat 5 }

gtmDnssecStatNsec3Resalt OBJECT-TYPE
	SYNTAX Counter64
	MAX-ACCESS read-only
	STATUS current
	DESCRIPTION
		"The number of times that salt was changed for NSEC3."
	::= { gtmGlobalDnssecStat 6 }

gtmDnssecStatDnssecResponses OBJECT-TYPE
	SYNTAX Counter64
	MAX-ACCESS read-only
	STATUS current
	DESCRIPTION
		"The number of signed responses."
	::= { gtmGlobalDnssecStat 7 }

gtmDnssecStatDnssecDnskeyQueries OBJECT-TYPE
	SYNTAX Counter64
	MAX-ACCESS read-only
	STATUS current
	DESCRIPTION
		"The number of queries for DNSKEY type."
	::= { gtmGlobalDnssecStat 8 }

gtmDnssecStatDnssecNsec3paramQueries OBJECT-TYPE
	SYNTAX Counter64
	MAX-ACCESS read-only
	STATUS current
	DESCRIPTION
		"The number of queries for NSEC3PARAM type."
	::= { gtmGlobalDnssecStat 9 }

gtmDnssecStatDnssecDsQueries OBJECT-TYPE
	SYNTAX Counter64
	MAX-ACCESS read-only
	STATUS current
	DESCRIPTION
		"The number of queries for DS type."
	::= { gtmGlobalDnssecStat 10 }

gtmDnssecStatSigCryptoFailed OBJECT-TYPE
	SYNTAX Counter64
	MAX-ACCESS read-only
	STATUS current
	DESCRIPTION
		"The number of signatures in which the cryptographic operation failed."
	::= { gtmGlobalDnssecStat 11 }

gtmDnssecStatSigSuccess OBJECT-TYPE
	SYNTAX Counter64
	MAX-ACCESS read-only
	STATUS current
	DESCRIPTION
		"The number of successfully generated signatures."
	::= { gtmGlobalDnssecStat 12 }

gtmDnssecStatSigFailed OBJECT-TYPE
	SYNTAX Counter64
	MAX-ACCESS read-only
	STATUS current
	DESCRIPTION
		"The number of general signature failures."
	::= { gtmGlobalDnssecStat 13 }

gtmDnssecStatSigRrsetFailed OBJECT-TYPE
	SYNTAX Counter64
	MAX-ACCESS read-only
	STATUS current
	DESCRIPTION
		"The number of failures due to an RRSET failing to be signed."
	::= { gtmGlobalDnssecStat 14 }

gtmDnssecStatConnectFlowFailed OBJECT-TYPE
	SYNTAX Counter64
	MAX-ACCESS read-only
	STATUS current
	DESCRIPTION
		"The number of connection flow failures."
	::= { gtmGlobalDnssecStat 15 }

gtmDnssecStatTowireFailed OBJECT-TYPE
	SYNTAX Counter64
	MAX-ACCESS read-only
	STATUS current
	DESCRIPTION
		"The number of failures when converting to a wire format packet."
	::= { gtmGlobalDnssecStat 16 }

gtmDnssecStatAxfrQueries OBJECT-TYPE
	SYNTAX Counter64
	MAX-ACCESS read-only
	STATUS current
	DESCRIPTION
		"The number of axfr queries."
	::= { gtmGlobalDnssecStat 17 }

gtmDnssecStatIxfrQueries OBJECT-TYPE
	SYNTAX Counter64
	MAX-ACCESS read-only
	STATUS current
	DESCRIPTION
		"The number of ixfr queries."
	::= { gtmGlobalDnssecStat 18 }

gtmDnssecStatXfrStarts OBJECT-TYPE
	SYNTAX Counter64
	MAX-ACCESS read-only
	STATUS current
	DESCRIPTION
		"The number of zone transfers which were started."
	::= { gtmGlobalDnssecStat 19 }

gtmDnssecStatXfrCompletes OBJECT-TYPE
	SYNTAX Counter64
	MAX-ACCESS read-only
	STATUS current
	DESCRIPTION
		"The number of zone transfers which were completed."
	::= { gtmGlobalDnssecStat 20 }

gtmDnssecStatXfrMsgs OBJECT-TYPE
	SYNTAX Counter64
	MAX-ACCESS read-only
	STATUS current
	DESCRIPTION
		"The number of zone transfer packets to clients."
	::= { gtmGlobalDnssecStat 21 }

gtmDnssecStatXfrMasterMsgs OBJECT-TYPE
	SYNTAX Counter64
	MAX-ACCESS read-only
	STATUS current
	DESCRIPTION
		"The number of zone transfer packets from the primary server."
	::= { gtmGlobalDnssecStat 22 }

gtmDnssecStatXfrResponseAverageSize OBJECT-TYPE
	SYNTAX Counter64
	MAX-ACCESS read-only
	STATUS current
	DESCRIPTION
		"Zone transfer average responses size in bytes."
	::= { gtmGlobalDnssecStat 23 }

gtmDnssecStatXfrSerial OBJECT-TYPE
	SYNTAX Counter64
	MAX-ACCESS read-only
	STATUS current
	DESCRIPTION
		"The serial number advertised to all clients."
	::= { gtmGlobalDnssecStat 24 }

gtmDnssecStatXfrMasterSerial OBJECT-TYPE
	SYNTAX Counter64
	MAX-ACCESS read-only
	STATUS current
	DESCRIPTION
		"The zone serial number of the primary server."
	::= { gtmGlobalDnssecStat 25 }

--==================================================================
-- Gtm_application_wideip
--==================================================================
gtmApplicationWideipNumber OBJECT-TYPE
	SYNTAX INTEGER
	MAX-ACCESS read-only
	STATUS current
	DESCRIPTION
		"The number of gtmApplicationWideip entries in the table."
	::= { gtmApplicationWideip 1 }

gtmApplicationWideipTable OBJECT-TYPE
	SYNTAX SEQUENCE OF GtmApplicationWideipEntry
	MAX-ACCESS not-accessible
	STATUS current
	DESCRIPTION
		"A table containing information on wide IPs associated with
		the specified applications for GTM (Global Traffic Management)."
	::= { gtmApplicationWideip 2 }

gtmApplicationWideipEntry OBJECT-TYPE
	SYNTAX  GtmApplicationWideipEntry
	MAX-ACCESS not-accessible
	STATUS current
	DESCRIPTION
		"Columns in the gtmApplicationWideip Table"
	INDEX {
		gtmApplicationWideipApplicationName,
		gtmApplicationWideipWipName,
		gtmApplicationWideipWipType
	}
	::= { gtmApplicationWideipTable 1 }

GtmApplicationWideipEntry ::=
	SEQUENCE {
        	gtmApplicationWideipApplicationName                       LongDisplayString,
        	gtmApplicationWideipWipName                               LongDisplayString,
        	gtmApplicationWideipWipType                               INTEGER
	}

gtmApplicationWideipApplicationName OBJECT-TYPE
	SYNTAX LongDisplayString
	MAX-ACCESS read-only
	STATUS current
	DESCRIPTION
		"The name of a GTM application."
	::= { gtmApplicationWideipEntry 1 }

gtmApplicationWideipWipName OBJECT-TYPE
	SYNTAX LongDisplayString
	MAX-ACCESS read-only
	STATUS current
	DESCRIPTION
		"The name of the wide IP associated with the GTM application."
	::= { gtmApplicationWideipEntry 2 }

gtmApplicationWideipWipType OBJECT-TYPE
	SYNTAX INTEGER {
		a(1),
		cname(5),
		mx(15),
		aaaa(28),
		srv(33),
		naptr(35)
	}
	MAX-ACCESS read-only
	STATUS current
	DESCRIPTION
		"The type of the wide IP associated with the GTM application."
	::= { gtmApplicationWideipEntry 3 }

--==================================================================
-- Gtm_device
--==================================================================
gtmDeviceNumber OBJECT-TYPE
	SYNTAX INTEGER
	MAX-ACCESS read-only
	STATUS current
	DESCRIPTION
		"The number of gtmDevice entries in the table."
	::= { gtmDevice 1 }

gtmDeviceTable OBJECT-TYPE
	SYNTAX SEQUENCE OF GtmDeviceEntry
	MAX-ACCESS not-accessible
	STATUS current
	DESCRIPTION
		"A table containing information on devices associated with a
		server for GTM (Global Traffic Management)."
	::= { gtmDevice 2 }

gtmDeviceEntry OBJECT-TYPE
	SYNTAX  GtmDeviceEntry
	MAX-ACCESS not-accessible
	STATUS current
	DESCRIPTION
		"Columns in the gtmDevice Table"
	INDEX {
		gtmDeviceServerName,
		gtmDeviceName
	}
	::= { gtmDeviceTable 1 }

GtmDeviceEntry ::=
	SEQUENCE {
        	gtmDeviceServerName                                       LongDisplayString,
        	gtmDeviceName                                             LongDisplayString
	}

gtmDeviceServerName OBJECT-TYPE
	SYNTAX LongDisplayString
	MAX-ACCESS read-only
	STATUS current
	DESCRIPTION
		"The name of the server associated with a device."
	::= { gtmDeviceEntry 1 }

gtmDeviceName OBJECT-TYPE
	SYNTAX LongDisplayString
	MAX-ACCESS read-only
	STATUS current
	DESCRIPTION
		"The name of a device."
	::= { gtmDeviceEntry 2 }

--==================================================================
-- Gtm_device_stat
--==================================================================
gtmDeviceStatResetStats OBJECT-TYPE
	SYNTAX INTEGER
	MAX-ACCESS read-write
	STATUS current
	DESCRIPTION
		"The action to reset resettable statistics data in gtmDeviceStat.
		 Setting this value to 1 will reset statistics data.
		 Note, some statistics data may not be reset including data that are incremental counters."
	::= { gtmDeviceStat 1 }

gtmDeviceStatNumber OBJECT-TYPE
	SYNTAX INTEGER
	MAX-ACCESS read-only
	STATUS current
	DESCRIPTION
		"The number of gtmDeviceStat entries in the table."
	::= { gtmDeviceStat 2 }

gtmDeviceStatTable OBJECT-TYPE
	SYNTAX SEQUENCE OF GtmDeviceStatEntry
	MAX-ACCESS not-accessible
	STATUS current
	DESCRIPTION
		"A table containing statistics information on devices associated with a
		 server for GTM (Global Traffic Management)."
	::= { gtmDeviceStat 3 }

gtmDeviceStatEntry OBJECT-TYPE
	SYNTAX  GtmDeviceStatEntry
	MAX-ACCESS not-accessible
	STATUS current
	DESCRIPTION
		"Columns in the gtmDeviceStat Table"
	INDEX {
		gtmDeviceStatServerName,
		gtmDeviceStatName
	}
	::= { gtmDeviceStatTable 1 }

GtmDeviceStatEntry ::=
	SEQUENCE {
        	gtmDeviceStatName                                         LongDisplayString,
        	gtmDeviceStatServerName                                   LongDisplayString,
        	gtmDeviceStatCpuUsage                                     Counter64,
        	gtmDeviceStatMemAvail                                     Counter64,
        	gtmDeviceStatBitsPerSecIn                                 Counter64,
        	gtmDeviceStatBitsPerSecOut                                Counter64,
        	gtmDeviceStatPktsPerSecIn                                 Counter64,
        	gtmDeviceStatPktsPerSecOut                                Counter64,
        	gtmDeviceStatConnections                                  Counter64
	}

gtmDeviceStatName OBJECT-TYPE
	SYNTAX LongDisplayString
	MAX-ACCESS read-only
	STATUS current
	DESCRIPTION
		"The name of a device."
	::= { gtmDeviceStatEntry 1 }

gtmDeviceStatServerName OBJECT-TYPE
	SYNTAX LongDisplayString
	MAX-ACCESS read-only
	STATUS current
	DESCRIPTION
		"The name of a server."
	::= { gtmDeviceStatEntry 2 }

gtmDeviceStatCpuUsage OBJECT-TYPE
	SYNTAX Counter64
	MAX-ACCESS read-only
	STATUS current
	DESCRIPTION
		"The CPU usage in percentage for the specified device."
	::= { gtmDeviceStatEntry 3 }

gtmDeviceStatMemAvail OBJECT-TYPE
	SYNTAX Counter64
	MAX-ACCESS read-only
	STATUS current
	DESCRIPTION
		"The memory available in bytes for the specified device."
	::= { gtmDeviceStatEntry 4 }

gtmDeviceStatBitsPerSecIn OBJECT-TYPE
	SYNTAX Counter64
	MAX-ACCESS read-only
	STATUS current
	DESCRIPTION
		"The number of bits per second received by the specified device."
	::= { gtmDeviceStatEntry 5 }

gtmDeviceStatBitsPerSecOut OBJECT-TYPE
	SYNTAX Counter64
	MAX-ACCESS read-only
	STATUS current
	DESCRIPTION
		"The number of bits per second sent from the specified device."
	::= { gtmDeviceStatEntry 6 }

gtmDeviceStatPktsPerSecIn OBJECT-TYPE
	SYNTAX Counter64
	MAX-ACCESS read-only
	STATUS current
	DESCRIPTION
		"The number of packets per second received by the specified device."
	::= { gtmDeviceStatEntry 7 }

gtmDeviceStatPktsPerSecOut OBJECT-TYPE
	SYNTAX Counter64
	MAX-ACCESS read-only
	STATUS current
	DESCRIPTION
		"The number of packets per second sent from the specified device."
	::= { gtmDeviceStatEntry 8 }

gtmDeviceStatConnections OBJECT-TYPE
	SYNTAX Counter64
	MAX-ACCESS read-only
	STATUS current
	DESCRIPTION
		"The number of total connections to the specified device."
	::= { gtmDeviceStatEntry 9 }

--==================================================================
-- Gtm_device_status
--==================================================================
gtmDeviceStatusNumber OBJECT-TYPE
	SYNTAX INTEGER
	MAX-ACCESS read-only
	STATUS current
	DESCRIPTION
		"The number of gtmDeviceStatus entries in the table."
	::= { gtmDeviceStatus 1 }

gtmDeviceStatusTable OBJECT-TYPE
	SYNTAX SEQUENCE OF GtmDeviceStatusEntry
	MAX-ACCESS not-accessible
	STATUS current
	DESCRIPTION
		"A table containing status information of devices within associated
		 server for GTM (Global Traffic Management)."
	::= { gtmDeviceStatus 2 }

gtmDeviceStatusEntry OBJECT-TYPE
	SYNTAX  GtmDeviceStatusEntry
	MAX-ACCESS not-accessible
	STATUS current
	DESCRIPTION
		"Columns in the gtmDeviceStatus Table"
	INDEX {
		gtmDeviceStatusServerName,
		gtmDeviceStatusName
	}
	::= { gtmDeviceStatusTable 1 }

GtmDeviceStatusEntry ::=
	SEQUENCE {
        	gtmDeviceStatusName                                       LongDisplayString,
        	gtmDeviceStatusServerName                                 LongDisplayString,
        	gtmDeviceStatusAvailState                                 INTEGER,
        	gtmDeviceStatusEnabledState                               INTEGER,
        	gtmDeviceStatusDetailReason                               LongDisplayString
	}

gtmDeviceStatusName OBJECT-TYPE
	SYNTAX LongDisplayString
	MAX-ACCESS read-only
	STATUS current
	DESCRIPTION
		"The name of a device."
	::= { gtmDeviceStatusEntry 1 }

gtmDeviceStatusServerName OBJECT-TYPE
	SYNTAX LongDisplayString
	MAX-ACCESS read-only
	STATUS current
	DESCRIPTION
		"The name of the server associated with a device."
	::= { gtmDeviceStatusEntry 2 }

gtmDeviceStatusAvailState OBJECT-TYPE
	SYNTAX INTEGER {
		none(0),
		green(1),
		yellow(2),
		red(3),
		blue(4),
		gray(5)
	}
	MAX-ACCESS read-only
	STATUS current
	DESCRIPTION
		"The availability of the specified device indicated by color.
	    none - error;
	    green - available in some capacity;
	    yellow - not currently available;
	    red - not available;
	    blue - availability is unknown;
	    gray - unlicensed."
	::= { gtmDeviceStatusEntry 3 }

gtmDeviceStatusEnabledState OBJECT-TYPE
	SYNTAX INTEGER {
		none(0),
		enabled(1),
		disabled(2),
		disabledbyparent(3)
	}
	MAX-ACCESS read-only
	STATUS current
	DESCRIPTION
		"The activity status of the specified device, as specified
	    by the user."
	::= { gtmDeviceStatusEntry 4 }

gtmDeviceStatusDetailReason OBJECT-TYPE
	SYNTAX LongDisplayString
	MAX-ACCESS read-only
	STATUS current
	DESCRIPTION
		"The detail description of the specified devices status."
	::= { gtmDeviceStatusEntry 5 }

--==================================================================
-- Gtm_device_ip
--==================================================================
gtmDeviceIpNumber OBJECT-TYPE
	SYNTAX INTEGER
	MAX-ACCESS read-only
	STATUS current
	DESCRIPTION
		"The number of gtmDeviceIp entries in the table."
	::= { gtmDeviceIp 1 }

gtmDeviceIpTable OBJECT-TYPE
	SYNTAX SEQUENCE OF GtmDeviceIpEntry
	MAX-ACCESS not-accessible
	STATUS current
	DESCRIPTION
		"A table containing information of device IPs for GTM (Global Traffic Management)."
	::= { gtmDeviceIp 2 }

gtmDeviceIpEntry OBJECT-TYPE
	SYNTAX  GtmDeviceIpEntry
	MAX-ACCESS not-accessible
	STATUS current
	DESCRIPTION
		"Columns in the gtmDeviceIp Table"
	INDEX {
		gtmDeviceIpServerName,
		gtmDeviceIpDeviceName,
		gtmDeviceIpIpType,
		gtmDeviceIpIp
	}
	::= { gtmDeviceIpTable 1 }

GtmDeviceIpEntry ::=
	SEQUENCE {
        	gtmDeviceIpServerName                                     LongDisplayString,
        	gtmDeviceIpDeviceName                                     LongDisplayString,
        	gtmDeviceIpIpType                                         InetAddressType,
        	gtmDeviceIpIp                                             InetAddress,
        	gtmDeviceIpIpXlatedType                                   InetAddressType,
        	gtmDeviceIpIpXlated                                       InetAddress
	}

gtmDeviceIpServerName OBJECT-TYPE
	SYNTAX LongDisplayString
	MAX-ACCESS read-only
	STATUS current
	DESCRIPTION
		"The name of the server associated with the specified device IP address."
	::= { gtmDeviceIpEntry 1 }

gtmDeviceIpDeviceName OBJECT-TYPE
	SYNTAX LongDisplayString
	MAX-ACCESS read-only
	STATUS current
	DESCRIPTION
		"The name of the device associated with the specified device IP address."
	::= { gtmDeviceIpEntry 2 }

gtmDeviceIpIpType OBJECT-TYPE
	SYNTAX InetAddressType
	MAX-ACCESS read-only
	STATUS current
	DESCRIPTION
		"The IP address type of gtmDeviceIpIp."
	::= { gtmDeviceIpEntry 3 }

gtmDeviceIpIp OBJECT-TYPE
	SYNTAX InetAddress
	MAX-ACCESS read-only
	STATUS current
	DESCRIPTION
		"The IP address that belongs to the specified device. It is interpreted
	    within the context of a gtmDeviceIpIpType value."
	::= { gtmDeviceIpEntry 4 }

gtmDeviceIpIpXlatedType OBJECT-TYPE
	SYNTAX InetAddressType
	MAX-ACCESS read-only
	STATUS current
	DESCRIPTION
		"The IP address type of gtmDeviceIpIpXlated."
	::= { gtmDeviceIpEntry 5 }

gtmDeviceIpIpXlated OBJECT-TYPE
	SYNTAX InetAddress
	MAX-ACCESS read-only
	STATUS current
	DESCRIPTION
		"The translated address for the specified device IP. It is interpreted
	    within the context of a gtmDeviceIpIpXlatedType value."
	::= { gtmDeviceIpEntry 6 }

--==================================================================
-- Gtm_link_ip
--==================================================================
gtmLinkIpNumber OBJECT-TYPE
	SYNTAX INTEGER
	MAX-ACCESS read-only
	STATUS current
	DESCRIPTION
		"The number of gtmLinkIp entries in the table."
	::= { gtmLinkIp 1 }

gtmLinkIpTable OBJECT-TYPE
	SYNTAX SEQUENCE OF GtmLinkIpEntry
	MAX-ACCESS not-accessible
	STATUS current
	DESCRIPTION
		"A table containing information of link IPs for GTM (Global Traffic Management)."
	::= { gtmLinkIp 2 }

gtmLinkIpEntry OBJECT-TYPE
	SYNTAX  GtmLinkIpEntry
	MAX-ACCESS not-accessible
	STATUS current
	DESCRIPTION
		"Columns in the gtmLinkIp Table"
	INDEX {
		gtmLinkIpLinkName,
		gtmLinkIpIpType,
		gtmLinkIpIp
	}
	::= { gtmLinkIpTable 1 }

GtmLinkIpEntry ::=
	SEQUENCE {
        	gtmLinkIpLinkName                                         LongDisplayString,
        	gtmLinkIpIpType                                           InetAddressType,
        	gtmLinkIpIp                                               InetAddress,
        	gtmLinkIpIpXlatedType                                     InetAddressType,
        	gtmLinkIpIpXlated                                         InetAddress
	}

gtmLinkIpLinkName OBJECT-TYPE
	SYNTAX LongDisplayString
	MAX-ACCESS read-only
	STATUS current
	DESCRIPTION
		"The link name associated with the specified link IP address."
	::= { gtmLinkIpEntry 1 }

gtmLinkIpIpType OBJECT-TYPE
	SYNTAX InetAddressType
	MAX-ACCESS read-only
	STATUS current
	DESCRIPTION
		"The IP address type of gtmLinkIpIp."
	::= { gtmLinkIpEntry 2 }

gtmLinkIpIp OBJECT-TYPE
	SYNTAX InetAddress
	MAX-ACCESS read-only
	STATUS current
	DESCRIPTION
		"The IP address that belongs to the specified link. It is interpreted
	    within the context of a gtmLinkIpIpType value."
	::= { gtmLinkIpEntry 3 }

gtmLinkIpIpXlatedType OBJECT-TYPE
	SYNTAX InetAddressType
	MAX-ACCESS read-only
	STATUS current
	DESCRIPTION
		"The IP address type of gtmLinkIpIpXlated."
	::= { gtmLinkIpEntry 4 }

gtmLinkIpIpXlated OBJECT-TYPE
	SYNTAX InetAddress
	MAX-ACCESS read-only
	STATUS current
	DESCRIPTION
		"The translated address for the specified link IP. It is interpreted
	    within the context of a gtmLinkIpIpXlatedType value."
	::= { gtmLinkIpEntry 5 }

--================================================================
 -- Compliance and Group
--================================================================

bigipGlobalTMCompliance	MODULE-COMPLIANCE
	STATUS current
	DESCRIPTION
		"This specifies the objects that are required to claim
                 compliance to F5 Traffic Management System."
	MODULE
	  MANDATORY-GROUPS { bigipGlobalTMGroups }
	::= { bigipCompliances 3 }

bigipGlobalTMGroups  OBJECT IDENTIFIER ::= {  bigipGroups 3 }

gtmAttrGroup OBJECT-GROUP
	 OBJECTS {
		gtmAttrDumpTopology,
		gtmAttrCacheLdns,
		gtmAttrAolAware,
		gtmAttrCheckStaticDepends,
		gtmAttrCheckDynamicDepends,
		gtmAttrDrainRequests,
		gtmAttrEnableResetsRipeness,
		gtmAttrFbRespectDepends,
		gtmAttrFbRespectAcl,
		gtmAttrDefaultAlternate,
		gtmAttrDefaultFallback,
		gtmAttrPersistMask,
		gtmAttrGtmSetsRecursion,
		gtmAttrQosFactorLcs,
		gtmAttrQosFactorRtt,
		gtmAttrQosFactorHops,
		gtmAttrQosFactorHitRatio,
		gtmAttrQosFactorPacketRate,
		gtmAttrQosFactorBps,
		gtmAttrQosFactorVsCapacity,
		gtmAttrQosFactorTopology,
		gtmAttrQosFactorConnRate,
		gtmAttrTimerRetryPathData,
		gtmAttrTimerGetAutoconfigData,
		gtmAttrTimerPersistCache,
		gtmAttrDefaultProbeLimit,
		gtmAttrDownThreshold,
		gtmAttrDownMultiple,
		gtmAttrPathTtl,
		gtmAttrTraceTtl,
		gtmAttrLdnsDuration,
		gtmAttrPathDuration,
		gtmAttrRttSampleCount,
		gtmAttrRttPacketLength,
		gtmAttrRttTimeout,
		gtmAttrMaxMonReqs,
		gtmAttrTraceroutePort,
		gtmAttrPathsNeverDie,
		gtmAttrProbeDisabledObjects,
		gtmAttrLinkLimitFactor,
		gtmAttrOverLimitLinkLimitFactor,
		gtmAttrLinkPrepaidFactor,
		gtmAttrLinkCompensateInbound,
		gtmAttrLinkCompensateOutbound,
		gtmAttrLinkCompensationHistory,
		gtmAttrMaxLinkOverLimitCount,
		gtmAttrLowerBoundPctRow,
		gtmAttrLowerBoundPctCol,
		gtmAttrAutoconf,
		gtmAttrAutosync,
		gtmAttrSyncNamedConf,
		gtmAttrSyncGroup,
		gtmAttrSyncTimeout,
		gtmAttrSyncZonesTimeout,
		gtmAttrTimeTolerance,
		gtmAttrTopologyLongestMatch,
		gtmAttrTopologyAclThreshold,
		gtmAttrStaticPersistCidr,
		gtmAttrStaticPersistV6Cidr,
		gtmAttrQosFactorVsScore,
		gtmAttrTimerSendKeepAlive,
		gtmAttrCertificateDepth,
		gtmAttrMaxMemoryUsage
	}
	STATUS	 current
	DESCRIPTION
		"A collection of objects of gtmGlobalAttr MIB."
	::= { bigipGlobalTMGroups 1 }

gtmGlobalLdnsProbeProtoGroup OBJECT-GROUP
	 OBJECTS {
		gtmGlobalLdnsProbeProtoNumber,
		gtmGlobalLdnsProbeProtoIndex,
		gtmGlobalLdnsProbeProtoType,
		gtmGlobalLdnsProbeProtoName
	}
	STATUS	 current
	DESCRIPTION
		"A collection of objects of gtmGlobalLdnsProbeProto MIB."
	::= { bigipGlobalTMGroups 2 }

gtmStatGroup OBJECT-GROUP
	 OBJECTS {
		gtmStatResetStats,
		gtmStatRequests,
		gtmStatResolutions,
		gtmStatPersisted,
		gtmStatPreferred,
		gtmStatAlternate,
		gtmStatFallback,
		gtmStatDropped,
		gtmStatExplicitIp,
		gtmStatReturnToDns,
		gtmStatReconnects,
		gtmStatBytesReceived,
		gtmStatBytesSent,
		gtmStatNumBacklogged,
		gtmStatBytesDropped,
		gtmStatLdnses,
		gtmStatPaths,
		gtmStatReturnFromDns,
		gtmStatCnameResolutions,
		gtmStatARequests,
		gtmStatAaaaRequests
	}
	STATUS	 current
	DESCRIPTION
		"A collection of objects of gtmGlobalStat MIB."
	::= { bigipGlobalTMGroups 3 }

gtmAppGroup OBJECT-GROUP
	 OBJECTS {
		gtmAppNumber,
		gtmAppName,
		gtmAppPersist,
		gtmAppTtlPersist,
		gtmAppAvailability
	}
	STATUS	 current
	DESCRIPTION
		"A collection of objects of gtmApplication MIB."
	::= { bigipGlobalTMGroups 4 }

gtmAppStatusGroup OBJECT-GROUP
	 OBJECTS {
		gtmAppStatusNumber,
		gtmAppStatusName,
		gtmAppStatusAvailState,
		gtmAppStatusEnabledState,
		gtmAppStatusParentType,
		gtmAppStatusDetailReason
	}
	STATUS	 current
	DESCRIPTION
		"A collection of objects of gtmApplicationStatus MIB."
	::= { bigipGlobalTMGroups 5 }

gtmAppContStatGroup OBJECT-GROUP
	 OBJECTS {
		gtmAppContStatNumber,
		gtmAppContStatAppName,
		gtmAppContStatType,
		gtmAppContStatName,
		gtmAppContStatNumAvail,
		gtmAppContStatAvailState,
		gtmAppContStatEnabledState,
		gtmAppContStatParentType,
		gtmAppContStatDetailReason
	}
	STATUS	 current
	DESCRIPTION
		"A collection of objects of gtmAppContextStat MIB."
	::= { bigipGlobalTMGroups 6 }

gtmAppContDisGroup OBJECT-GROUP
	 OBJECTS {
		gtmAppContDisNumber,
		gtmAppContDisAppName,
		gtmAppContDisType,
		gtmAppContDisName
	}
	STATUS	 current
	DESCRIPTION
		"A collection of objects of gtmAppContextDisable MIB."
	::= { bigipGlobalTMGroups 7 }

gtmDcGroup OBJECT-GROUP
	 OBJECTS {
		gtmDcNumber,
		gtmDcName,
		gtmDcLocation,
		gtmDcContact,
		gtmDcEnabled
	}
	STATUS	 current
	DESCRIPTION
		"A collection of objects of gtmDataCenter MIB."
	::= { bigipGlobalTMGroups 8 }

gtmDcStatGroup OBJECT-GROUP
	 OBJECTS {
		gtmDcStatResetStats,
		gtmDcStatNumber,
		gtmDcStatName,
		gtmDcStatCpuUsage,
		gtmDcStatMemAvail,
		gtmDcStatBitsPerSecIn,
		gtmDcStatBitsPerSecOut,
		gtmDcStatPktsPerSecIn,
		gtmDcStatPktsPerSecOut,
		gtmDcStatConnections,
		gtmDcStatConnRate
	}
	STATUS	 current
	DESCRIPTION
		"A collection of objects of gtmDataCenterStat MIB."
	::= { bigipGlobalTMGroups 9 }

gtmDcStatusGroup OBJECT-GROUP
	 OBJECTS {
		gtmDcStatusNumber,
		gtmDcStatusName,
		gtmDcStatusAvailState,
		gtmDcStatusEnabledState,
		gtmDcStatusParentType,
		gtmDcStatusDetailReason
	}
	STATUS	 current
	DESCRIPTION
		"A collection of objects of gtmDataCenterStatus MIB."
	::= { bigipGlobalTMGroups 10 }

gtmIpGroup OBJECT-GROUP
	 OBJECTS {
		gtmIpNumber,
		gtmIpIpType,
		gtmIpIp,
		gtmIpLinkName,
		gtmIpServerName,
		gtmIpUnitId,
		gtmIpIpXlatedType,
		gtmIpIpXlated,
		gtmIpDeviceName
	}
	STATUS	 current
	DESCRIPTION
		"A collection of objects of gtmIp MIB."
	::= { bigipGlobalTMGroups 11 }

gtmLinkGroup OBJECT-GROUP
	 OBJECTS {
		gtmLinkNumber,
		gtmLinkName,
		gtmLinkDcName,
		gtmLinkIspName,
		gtmLinkUplinkAddressType,
		gtmLinkUplinkAddress,
		gtmLinkLimitInCpuUsageEnabled,
		gtmLinkLimitInMemAvailEnabled,
		gtmLinkLimitInBitsPerSecEnabled,
		gtmLinkLimitInPktsPerSecEnabled,
		gtmLinkLimitInConnEnabled,
		gtmLinkLimitInConnPerSecEnabled,
		gtmLinkLimitInCpuUsage,
		gtmLinkLimitInMemAvail,
		gtmLinkLimitInBitsPerSec,
		gtmLinkLimitInPktsPerSec,
		gtmLinkLimitInConn,
		gtmLinkLimitInConnPerSec,
		gtmLinkLimitOutCpuUsageEnabled,
		gtmLinkLimitOutMemAvailEnabled,
		gtmLinkLimitOutBitsPerSecEnabled,
		gtmLinkLimitOutPktsPerSecEnabled,
		gtmLinkLimitOutConnEnabled,
		gtmLinkLimitOutConnPerSecEnabled,
		gtmLinkLimitOutCpuUsage,
		gtmLinkLimitOutMemAvail,
		gtmLinkLimitOutBitsPerSec,
		gtmLinkLimitOutPktsPerSec,
		gtmLinkLimitOutConn,
		gtmLinkLimitOutConnPerSec,
		gtmLinkLimitTotalCpuUsageEnabled,
		gtmLinkLimitTotalMemAvailEnabled,
		gtmLinkLimitTotalBitsPerSecEnabled,
		gtmLinkLimitTotalPktsPerSecEnabled,
		gtmLinkLimitTotalConnEnabled,
		gtmLinkLimitTotalConnPerSecEnabled,
		gtmLinkLimitTotalCpuUsage,
		gtmLinkLimitTotalMemAvail,
		gtmLinkLimitTotalBitsPerSec,
		gtmLinkLimitTotalPktsPerSec,
		gtmLinkLimitTotalConn,
		gtmLinkLimitTotalConnPerSec,
		gtmLinkMonitorRule,
		gtmLinkDuplex,
		gtmLinkEnabled,
		gtmLinkRatio,
		gtmLinkPrepaid,
		gtmLinkPrepaidInDollars,
		gtmLinkWeightingType
	}
	STATUS	 current
	DESCRIPTION
		"A collection of objects of gtmLink MIB."
	::= { bigipGlobalTMGroups 12 }

gtmLinkCostGroup OBJECT-GROUP
	 OBJECTS {
		gtmLinkCostNumber,
		gtmLinkCostName,
		gtmLinkCostIndex,
		gtmLinkCostUptoBps,
		gtmLinkCostDollarsPerMbps
	}
	STATUS	 current
	DESCRIPTION
		"A collection of objects of gtmLinkCost MIB."
	::= { bigipGlobalTMGroups 13 }

gtmLinkStatGroup OBJECT-GROUP
	 OBJECTS {
		gtmLinkStatResetStats,
		gtmLinkStatNumber,
		gtmLinkStatName,
		gtmLinkStatRate,
		gtmLinkStatRateIn,
		gtmLinkStatRateOut,
		gtmLinkStatRateNode,
		gtmLinkStatRateNodeIn,
		gtmLinkStatRateNodeOut,
		gtmLinkStatRateVses,
		gtmLinkStatRateVsesIn,
		gtmLinkStatRateVsesOut,
		gtmLinkStatLcsIn,
		gtmLinkStatLcsOut,
		gtmLinkStatPaths
	}
	STATUS	 current
	DESCRIPTION
		"A collection of objects of gtmLinkStat MIB."
	::= { bigipGlobalTMGroups 14 }

gtmLinkStatusGroup OBJECT-GROUP
	 OBJECTS {
		gtmLinkStatusNumber,
		gtmLinkStatusName,
		gtmLinkStatusAvailState,
		gtmLinkStatusEnabledState,
		gtmLinkStatusParentType,
		gtmLinkStatusDetailReason
	}
	STATUS	 current
	DESCRIPTION
		"A collection of objects of gtmLinkStatus MIB."
	::= { bigipGlobalTMGroups 15 }

gtmPoolGroup OBJECT-GROUP
	 OBJECTS {
		gtmPoolNumber,
		gtmPoolName,
		gtmPoolTtl,
		gtmPoolEnabled,
		gtmPoolVerifyMember,
		gtmPoolDynamicRatio,
		gtmPoolAnswersToReturn,
		gtmPoolLbMode,
		gtmPoolAlternate,
		gtmPoolFallback,
		gtmPoolManualResume,
		gtmPoolQosCoeffRtt,
		gtmPoolQosCoeffHops,
		gtmPoolQosCoeffTopology,
		gtmPoolQosCoeffHitRatio,
		gtmPoolQosCoeffPacketRate,
		gtmPoolQosCoeffVsCapacity,
		gtmPoolQosCoeffBps,
		gtmPoolQosCoeffLcs,
		gtmPoolQosCoeffConnRate,
		gtmPoolFallbackIpType,
		gtmPoolFallbackIp,
		gtmPoolCname,
		gtmPoolLimitCpuUsageEnabled,
		gtmPoolLimitMemAvailEnabled,
		gtmPoolLimitBitsPerSecEnabled,
		gtmPoolLimitPktsPerSecEnabled,
		gtmPoolLimitConnEnabled,
		gtmPoolLimitConnPerSecEnabled,
		gtmPoolLimitCpuUsage,
		gtmPoolLimitMemAvail,
		gtmPoolLimitBitsPerSec,
		gtmPoolLimitPktsPerSec,
		gtmPoolLimitConn,
		gtmPoolLimitConnPerSec,
		gtmPoolMonitorRule,
		gtmPoolQosCoeffVsScore,
		gtmPoolFallbackIpv6Type,
		gtmPoolFallbackIpv6,
		gtmPoolPoolType
	}
	STATUS	 current
	DESCRIPTION
		"A collection of objects of gtmPool MIB."
	::= { bigipGlobalTMGroups 16 }

gtmPoolStatGroup OBJECT-GROUP
	 OBJECTS {
		gtmPoolStatResetStats,
		gtmPoolStatNumber,
		gtmPoolStatName,
		gtmPoolStatPreferred,
		gtmPoolStatAlternate,
		gtmPoolStatFallback,
		gtmPoolStatDropped,
		gtmPoolStatExplicitIp,
		gtmPoolStatReturnToDns,
		gtmPoolStatReturnFromDns,
		gtmPoolStatCnameResolutions,
		gtmPoolStatPoolType
	}
	STATUS	 current
	DESCRIPTION
		"A collection of objects of gtmPoolStat MIB."
	::= { bigipGlobalTMGroups 17 }

gtmPoolMbrGroup OBJECT-GROUP
	 OBJECTS {
		gtmPoolMbrNumber,
		gtmPoolMbrPoolName,
		gtmPoolMbrIpType,
		gtmPoolMbrIp,
		gtmPoolMbrPort,
		gtmPoolMbrVsName,
		gtmPoolMbrOrder,
		gtmPoolMbrLimitCpuUsageEnabled,
		gtmPoolMbrLimitMemAvailEnabled,
		gtmPoolMbrLimitBitsPerSecEnabled,
		gtmPoolMbrLimitPktsPerSecEnabled,
		gtmPoolMbrLimitConnEnabled,
		gtmPoolMbrLimitConnPerSecEnabled,
		gtmPoolMbrLimitCpuUsage,
		gtmPoolMbrLimitMemAvail,
		gtmPoolMbrLimitBitsPerSec,
		gtmPoolMbrLimitPktsPerSec,
		gtmPoolMbrLimitConn,
		gtmPoolMbrLimitConnPerSec,
		gtmPoolMbrMonitorRule,
		gtmPoolMbrEnabled,
		gtmPoolMbrRatio,
		gtmPoolMbrServerName,
		gtmPoolMbrPoolType,
		gtmPoolMbrStaticTarget,
		gtmPoolMbrRdataPriority,
		gtmPoolMbrRdataWeight,
		gtmPoolMbrRdataPort,
		gtmPoolMbrRdataOrder,
		gtmPoolMbrRdataPreference,
		gtmPoolMbrRdataFlags,
		gtmPoolMbrRdataService
	}
	STATUS	 current
	DESCRIPTION
		"A collection of objects of gtmPoolMember MIB."
	::= { bigipGlobalTMGroups 18 }

gtmPoolStatusGroup OBJECT-GROUP
	 OBJECTS {
		gtmPoolStatusNumber,
		gtmPoolStatusName,
		gtmPoolStatusAvailState,
		gtmPoolStatusEnabledState,
		gtmPoolStatusParentType,
		gtmPoolStatusDetailReason,
		gtmPoolStatusPoolType
	}
	STATUS	 current
	DESCRIPTION
		"A collection of objects of gtmPoolStatus MIB."
	::= { bigipGlobalTMGroups 19 }

gtmPoolMbrDepsGroup OBJECT-GROUP
	 OBJECTS {
		gtmPoolMbrDepsNumber,
		gtmPoolMbrDepsIpType,
		gtmPoolMbrDepsIp,
		gtmPoolMbrDepsPort,
		gtmPoolMbrDepsPoolName,
		gtmPoolMbrDepsVipType,
		gtmPoolMbrDepsVip,
		gtmPoolMbrDepsVport,
		gtmPoolMbrDepsServerName,
		gtmPoolMbrDepsVsName,
		gtmPoolMbrDepsDependServerName,
		gtmPoolMbrDepsDependVsName,
		gtmPoolMbrDepsPoolType
	}
	STATUS	 current
	DESCRIPTION
		"A collection of objects of gtmPoolMemberDepends MIB."
	::= { bigipGlobalTMGroups 20 }

gtmPoolMbrStatGroup OBJECT-GROUP
	 OBJECTS {
		gtmPoolMbrStatResetStats,
		gtmPoolMbrStatNumber,
		gtmPoolMbrStatPoolName,
		gtmPoolMbrStatIpType,
		gtmPoolMbrStatIp,
		gtmPoolMbrStatPort,
		gtmPoolMbrStatPreferred,
		gtmPoolMbrStatAlternate,
		gtmPoolMbrStatFallback,
		gtmPoolMbrStatServerName,
		gtmPoolMbrStatVsName,
		gtmPoolMbrStatPoolType
	}
	STATUS	 current
	DESCRIPTION
		"A collection of objects of gtmPoolMemberStat MIB."
	::= { bigipGlobalTMGroups 21 }

gtmPoolMbrStatusGroup OBJECT-GROUP
	 OBJECTS {
		gtmPoolMbrStatusNumber,
		gtmPoolMbrStatusPoolName,
		gtmPoolMbrStatusIpType,
		gtmPoolMbrStatusIp,
		gtmPoolMbrStatusPort,
		gtmPoolMbrStatusAvailState,
		gtmPoolMbrStatusEnabledState,
		gtmPoolMbrStatusParentType,
		gtmPoolMbrStatusDetailReason,
		gtmPoolMbrStatusVsName,
		gtmPoolMbrStatusServerName,
		gtmPoolMbrStatusPoolType
	}
	STATUS	 current
	DESCRIPTION
		"A collection of objects of gtmPoolMemberStatus MIB."
	::= { bigipGlobalTMGroups 22 }

gtmRegionEntryGroup OBJECT-GROUP
	 OBJECTS {
		gtmRegionEntryNumber,
		gtmRegionEntryName,
		gtmRegionEntryRegionDbType
	}
	STATUS	 current
	DESCRIPTION
		"A collection of objects of gtmRegionEntry MIB."
	::= { bigipGlobalTMGroups 23 }

gtmRegItemGroup OBJECT-GROUP
	 OBJECTS {
		gtmRegItemNumber,
		gtmRegItemRegionDbType,
		gtmRegItemRegionName,
		gtmRegItemType,
		gtmRegItemNegate,
		gtmRegItemRegEntry
	}
	STATUS	 current
	DESCRIPTION
		"A collection of objects of gtmRegItem MIB."
	::= { bigipGlobalTMGroups 24 }

gtmRuleGroup OBJECT-GROUP
	 OBJECTS {
		gtmRuleNumber,
		gtmRuleName,
		gtmRuleDefinition,
		gtmRuleConfigSource
	}
	STATUS	 current
	DESCRIPTION
		"A collection of objects of gtmRule MIB."
	::= { bigipGlobalTMGroups 25 }

gtmRuleEventGroup OBJECT-GROUP
	 OBJECTS {
		gtmRuleEventNumber,
		gtmRuleEventName,
		gtmRuleEventEventType,
		gtmRuleEventPriority,
		gtmRuleEventScript
	}
	STATUS	 current
	DESCRIPTION
		"A collection of objects of gtmRuleEvent MIB."
	::= { bigipGlobalTMGroups 26 }

gtmRuleEventStatGroup OBJECT-GROUP
	 OBJECTS {
		gtmRuleEventStatResetStats,
		gtmRuleEventStatNumber,
		gtmRuleEventStatName,
		gtmRuleEventStatEventType,
		gtmRuleEventStatPriority,
		gtmRuleEventStatFailures,
		gtmRuleEventStatAborts,
		gtmRuleEventStatTotalExecutions
	}
	STATUS	 current
	DESCRIPTION
		"A collection of objects of gtmRuleEventStat MIB."
	::= { bigipGlobalTMGroups 27 }

gtmServerGroup OBJECT-GROUP
	 OBJECTS {
		gtmServerNumber,
		gtmServerName,
		gtmServerDcName,
		gtmServerType,
		gtmServerEnabled,
		gtmServerLimitCpuUsageEnabled,
		gtmServerLimitMemAvailEnabled,
		gtmServerLimitBitsPerSecEnabled,
		gtmServerLimitPktsPerSecEnabled,
		gtmServerLimitConnEnabled,
		gtmServerLimitConnPerSecEnabled,
		gtmServerLimitCpuUsage,
		gtmServerLimitMemAvail,
		gtmServerLimitBitsPerSec,
		gtmServerLimitPktsPerSec,
		gtmServerLimitConn,
		gtmServerLimitConnPerSec,
		gtmServerProberType,
		gtmServerProber,
		gtmServerMonitorRule,
		gtmServerAllowSvcChk,
		gtmServerAllowPath,
		gtmServerAllowSnmp,
		gtmServerAutoconfState,
		gtmServerLinkAutoconfState
	}
	STATUS	 current
	DESCRIPTION
		"A collection of objects of gtmServer MIB."
	::= { bigipGlobalTMGroups 28 }

gtmServerStatGroup OBJECT-GROUP
	 OBJECTS {
		gtmServerStatResetStats,
		gtmServerStatNumber,
		gtmServerStatName,
		gtmServerStatUnitId,
		gtmServerStatVsPicks,
		gtmServerStatCpuUsage,
		gtmServerStatMemAvail,
		gtmServerStatBitsPerSecIn,
		gtmServerStatBitsPerSecOut,
		gtmServerStatPktsPerSecIn,
		gtmServerStatPktsPerSecOut,
		gtmServerStatConnections,
		gtmServerStatConnRate
	}
	STATUS	 current
	DESCRIPTION
		"A collection of objects of gtmServerStat MIB."
	::= { bigipGlobalTMGroups 29 }

gtmServerStatusGroup OBJECT-GROUP
	 OBJECTS {
		gtmServerStatusNumber,
		gtmServerStatusName,
		gtmServerStatusAvailState,
		gtmServerStatusEnabledState,
		gtmServerStatusParentType,
		gtmServerStatusDetailReason
	}
	STATUS	 current
	DESCRIPTION
		"A collection of objects of gtmServerStatus MIB."
	::= { bigipGlobalTMGroups 30 }

gtmTopItemGroup OBJECT-GROUP
	 OBJECTS {
		gtmTopItemNumber,
		gtmTopItemLdnsType,
		gtmTopItemLdnsNegate,
		gtmTopItemLdnsEntry,
		gtmTopItemServerType,
		gtmTopItemServerNegate,
		gtmTopItemServerEntry,
		gtmTopItemWeight,
		gtmTopItemOrder
	}
	STATUS	 current
	DESCRIPTION
		"A collection of objects of gtmTopItem MIB."
	::= { bigipGlobalTMGroups 31 }

gtmVsGroup OBJECT-GROUP
	 OBJECTS {
		gtmVsNumber,
		gtmVsIpType,
		gtmVsIp,
		gtmVsPort,
		gtmVsName,
		gtmVsServerName,
		gtmVsIpXlatedType,
		gtmVsIpXlated,
		gtmVsPortXlated,
		gtmVsLimitCpuUsageEnabled,
		gtmVsLimitMemAvailEnabled,
		gtmVsLimitBitsPerSecEnabled,
		gtmVsLimitPktsPerSecEnabled,
		gtmVsLimitConnEnabled,
		gtmVsLimitConnPerSecEnabled,
		gtmVsLimitCpuUsage,
		gtmVsLimitMemAvail,
		gtmVsLimitBitsPerSec,
		gtmVsLimitPktsPerSec,
		gtmVsLimitConn,
		gtmVsLimitConnPerSec,
		gtmVsMonitorRule,
		gtmVsEnabled,
		gtmVsLinkName,
		gtmVsLtmName
	}
	STATUS	 current
	DESCRIPTION
		"A collection of objects of gtmVirtualServ MIB."
	::= { bigipGlobalTMGroups 32 }

gtmVsDepsGroup OBJECT-GROUP
	 OBJECTS {
		gtmVsDepsNumber,
		gtmVsDepsIpType,
		gtmVsDepsIp,
		gtmVsDepsPort,
		gtmVsDepsVipType,
		gtmVsDepsVip,
		gtmVsDepsVport,
		gtmVsDepsServerName,
		gtmVsDepsVsName,
		gtmVsDepsDependServerName,
		gtmVsDepsDependVsName
	}
	STATUS	 current
	DESCRIPTION
		"A collection of objects of gtmVirtualServDepends MIB."
	::= { bigipGlobalTMGroups 33 }

gtmVsStatGroup OBJECT-GROUP
	 OBJECTS {
		gtmVsStatResetStats,
		gtmVsStatNumber,
		gtmVsStatIpType,
		gtmVsStatIp,
		gtmVsStatPort,
		gtmVsStatName,
		gtmVsStatCpuUsage,
		gtmVsStatMemAvail,
		gtmVsStatBitsPerSecIn,
		gtmVsStatBitsPerSecOut,
		gtmVsStatPktsPerSecIn,
		gtmVsStatPktsPerSecOut,
		gtmVsStatConnections,
		gtmVsStatConnRate,
		gtmVsStatVsScore,
		gtmVsStatServerName
	}
	STATUS	 current
	DESCRIPTION
		"A collection of objects of gtmVirtualServStat MIB."
	::= { bigipGlobalTMGroups 34 }

gtmVsStatusGroup OBJECT-GROUP
	 OBJECTS {
		gtmVsStatusNumber,
		gtmVsStatusIpType,
		gtmVsStatusIp,
		gtmVsStatusPort,
		gtmVsStatusAvailState,
		gtmVsStatusEnabledState,
		gtmVsStatusParentType,
		gtmVsStatusDetailReason,
		gtmVsStatusVsName,
		gtmVsStatusServerName
	}
	STATUS	 current
	DESCRIPTION
		"A collection of objects of gtmVirtualServStatus MIB."
	::= { bigipGlobalTMGroups 35 }

gtmWideipGroup OBJECT-GROUP
	 OBJECTS {
		gtmWideipNumber,
		gtmWideipName,
		gtmWideipPersist,
		gtmWideipTtlPersist,
		gtmWideipEnabled,
		gtmWideipLbmodePool,
		gtmWideipApplication,
		gtmWideipLastResortPool,
		gtmWideipIpNoError,
		gtmWideipLoadBalancingDecisionLogVerbosity,
		gtmWideipIpNoErrorTtl,
		gtmWideipPersistCidr,
		gtmWideipPersistV6Cidr,
		gtmWideipMinimalResponse,
		gtmWideipType,
		gtmWideipLastResortPoolType
	}
	STATUS	 current
	DESCRIPTION
		"A collection of objects of gtmWideip MIB."
	::= { bigipGlobalTMGroups 36 }

gtmWideipStatGroup OBJECT-GROUP
	 OBJECTS {
		gtmWideipStatResetStats,
		gtmWideipStatNumber,
		gtmWideipStatName,
		gtmWideipStatRequests,
		gtmWideipStatResolutions,
		gtmWideipStatPersisted,
		gtmWideipStatPreferred,
		gtmWideipStatFallback,
		gtmWideipStatDropped,
		gtmWideipStatExplicitIp,
		gtmWideipStatReturnToDns,
		gtmWideipStatReturnFromDns,
		gtmWideipStatCnameResolutions,
		gtmWideipStatARequests,
		gtmWideipStatAaaaRequests,
		gtmWideipStatAlternate,
		gtmWideipStatWipType
	}
	STATUS	 current
	DESCRIPTION
		"A collection of objects of gtmWideipStat MIB."
	::= { bigipGlobalTMGroups 37 }

gtmWideipStatusGroup OBJECT-GROUP
	 OBJECTS {
		gtmWideipStatusNumber,
		gtmWideipStatusName,
		gtmWideipStatusAvailState,
		gtmWideipStatusEnabledState,
		gtmWideipStatusParentType,
		gtmWideipStatusDetailReason,
		gtmWideipStatusType
	}
	STATUS	 current
	DESCRIPTION
		"A collection of objects of gtmWideipStatus MIB."
	::= { bigipGlobalTMGroups 38 }

gtmWideipAliasGroup OBJECT-GROUP
	 OBJECTS {
		gtmWideipAliasNumber,
		gtmWideipAliasWipName,
		gtmWideipAliasName,
		gtmWideipAliasWipType
	}
	STATUS	 current
	DESCRIPTION
		"A collection of objects of gtmWideipAlias MIB."
	::= { bigipGlobalTMGroups 39 }

gtmWideipPoolGroup OBJECT-GROUP
	 OBJECTS {
		gtmWideipPoolNumber,
		gtmWideipPoolWipName,
		gtmWideipPoolPoolName,
		gtmWideipPoolOrder,
		gtmWideipPoolRatio,
		gtmWideipPoolWipType,
		gtmWideipPoolPoolType
	}
	STATUS	 current
	DESCRIPTION
		"A collection of objects of gtmWideipPool MIB."
	::= { bigipGlobalTMGroups 40 }

gtmWideipRuleGroup OBJECT-GROUP
	 OBJECTS {
		gtmWideipRuleNumber,
		gtmWideipRuleWipName,
		gtmWideipRuleRuleName,
		gtmWideipRulePriority,
		gtmWideipRuleWipType
	}
	STATUS	 current
	DESCRIPTION
		"A collection of objects of gtmWideipRule MIB."
	::= { bigipGlobalTMGroups 41 }

gtmServerStat2Group OBJECT-GROUP
	 OBJECTS {
		gtmServerStat2ResetStats,
		gtmServerStat2Number,
		gtmServerStat2Name,
		gtmServerStat2UnitId,
		gtmServerStat2VsPicks,
		gtmServerStat2CpuUsage,
		gtmServerStat2MemAvail,
		gtmServerStat2BitsPerSecIn,
		gtmServerStat2BitsPerSecOut,
		gtmServerStat2PktsPerSecIn,
		gtmServerStat2PktsPerSecOut,
		gtmServerStat2Connections,
		gtmServerStat2ConnRate
	}
	STATUS	 current
	DESCRIPTION
		"A collection of objects of gtmServerStat2 MIB."
	::= { bigipGlobalTMGroups 42 }

gtmProberPoolGroup OBJECT-GROUP
	 OBJECTS {
		gtmProberPoolNumber,
		gtmProberPoolName,
		gtmProberPoolLbMode,
		gtmProberPoolEnabled
	}
	STATUS	 current
	DESCRIPTION
		"A collection of objects of gtmProberPool MIB."
	::= { bigipGlobalTMGroups 43 }

gtmProberPoolStatGroup OBJECT-GROUP
	 OBJECTS {
		gtmProberPoolStatResetStats,
		gtmProberPoolStatNumber,
		gtmProberPoolStatName,
		gtmProberPoolStatTotalProbes,
		gtmProberPoolStatSuccessfulProbes,
		gtmProberPoolStatFailedProbes
	}
	STATUS	 current
	DESCRIPTION
		"A collection of objects of gtmProberPoolStat MIB."
	::= { bigipGlobalTMGroups 44 }

gtmProberPoolStatusGroup OBJECT-GROUP
	 OBJECTS {
		gtmProberPoolStatusNumber,
		gtmProberPoolStatusName,
		gtmProberPoolStatusAvailState,
		gtmProberPoolStatusEnabledState,
		gtmProberPoolStatusDetailReason
	}
	STATUS	 current
	DESCRIPTION
		"A collection of objects of gtmProberPoolStatus MIB."
	::= { bigipGlobalTMGroups 45 }

gtmProberPoolMbrGroup OBJECT-GROUP
	 OBJECTS {
		gtmProberPoolMbrNumber,
		gtmProberPoolMbrPoolName,
		gtmProberPoolMbrServerName,
		gtmProberPoolMbrPmbrOrder,
		gtmProberPoolMbrEnabled
	}
	STATUS	 current
	DESCRIPTION
		"A collection of objects of gtmProberPoolMember MIB."
	::= { bigipGlobalTMGroups 46 }

gtmProberPoolMbrStatGroup OBJECT-GROUP
	 OBJECTS {
		gtmProberPoolMbrStatResetStats,
		gtmProberPoolMbrStatNumber,
		gtmProberPoolMbrStatPoolName,
		gtmProberPoolMbrStatServerName,
		gtmProberPoolMbrStatTotalProbes,
		gtmProberPoolMbrStatSuccessfulProbes,
		gtmProberPoolMbrStatFailedProbes
	}
	STATUS	 current
	DESCRIPTION
		"A collection of objects of gtmProberPoolMemberStat MIB."
	::= { bigipGlobalTMGroups 47 }

gtmProberPoolMbrStatusGroup OBJECT-GROUP
	 OBJECTS {
		gtmProberPoolMbrStatusNumber,
		gtmProberPoolMbrStatusPoolName,
		gtmProberPoolMbrStatusServerName,
		gtmProberPoolMbrStatusAvailState,
		gtmProberPoolMbrStatusEnabledState,
		gtmProberPoolMbrStatusDetailReason
	}
	STATUS	 current
	DESCRIPTION
		"A collection of objects of gtmProberPoolMemberStatus MIB."
	::= { bigipGlobalTMGroups 48 }

gtmAttr2Group OBJECT-GROUP
	 OBJECTS {
		gtmAttr2Number,
		gtmAttr2DumpTopology,
		gtmAttr2CacheLdns,
		gtmAttr2AolAware,
		gtmAttr2CheckStaticDepends,
		gtmAttr2CheckDynamicDepends,
		gtmAttr2DrainRequests,
		gtmAttr2EnableResetsRipeness,
		gtmAttr2FbRespectDepends,
		gtmAttr2FbRespectAcl,
		gtmAttr2DefaultAlternate,
		gtmAttr2DefaultFallback,
		gtmAttr2PersistMask,
		gtmAttr2GtmSetsRecursion,
		gtmAttr2QosFactorLcs,
		gtmAttr2QosFactorRtt,
		gtmAttr2QosFactorHops,
		gtmAttr2QosFactorHitRatio,
		gtmAttr2QosFactorPacketRate,
		gtmAttr2QosFactorBps,
		gtmAttr2QosFactorVsCapacity,
		gtmAttr2QosFactorTopology,
		gtmAttr2QosFactorConnRate,
		gtmAttr2TimerRetryPathData,
		gtmAttr2TimerGetAutoconfigData,
		gtmAttr2TimerPersistCache,
		gtmAttr2DefaultProbeLimit,
		gtmAttr2DownThreshold,
		gtmAttr2DownMultiple,
		gtmAttr2PathTtl,
		gtmAttr2TraceTtl,
		gtmAttr2LdnsDuration,
		gtmAttr2PathDuration,
		gtmAttr2RttSampleCount,
		gtmAttr2RttPacketLength,
		gtmAttr2RttTimeout,
		gtmAttr2MaxMonReqs,
		gtmAttr2TraceroutePort,
		gtmAttr2PathsNeverDie,
		gtmAttr2ProbeDisabledObjects,
		gtmAttr2LinkLimitFactor,
		gtmAttr2OverLimitLinkLimitFactor,
		gtmAttr2LinkPrepaidFactor,
		gtmAttr2LinkCompensateInbound,
		gtmAttr2LinkCompensateOutbound,
		gtmAttr2LinkCompensationHistory,
		gtmAttr2MaxLinkOverLimitCount,
		gtmAttr2LowerBoundPctRow,
		gtmAttr2LowerBoundPctCol,
		gtmAttr2Autoconf,
		gtmAttr2Autosync,
		gtmAttr2SyncNamedConf,
		gtmAttr2SyncGroup,
		gtmAttr2SyncTimeout,
		gtmAttr2SyncZonesTimeout,
		gtmAttr2TimeTolerance,
		gtmAttr2TopologyLongestMatch,
		gtmAttr2TopologyAclThreshold,
		gtmAttr2StaticPersistCidr,
		gtmAttr2StaticPersistV6Cidr,
		gtmAttr2QosFactorVsScore,
		gtmAttr2TimerSendKeepAlive,
		gtmAttr2CertificateDepth,
		gtmAttr2MaxMemoryUsage,
		gtmAttr2Name,
		gtmAttr2ForwardStatus
	}
	STATUS	 current
	DESCRIPTION
		"A collection of objects of gtmGlobalAttr2 MIB."
	::= { bigipGlobalTMGroups 49 }

gtmDnssecZoneStatGroup OBJECT-GROUP
	 OBJECTS {
		gtmDnssecZoneStatResetStats,
		gtmDnssecZoneStatNumber,
		gtmDnssecZoneStatName,
		gtmDnssecZoneStatNsec3s,
		gtmDnssecZoneStatNsec3Nodata,
		gtmDnssecZoneStatNsec3Nxdomain,
		gtmDnssecZoneStatNsec3Referral,
		gtmDnssecZoneStatNsec3Resalt,
		gtmDnssecZoneStatDnssecResponses,
		gtmDnssecZoneStatDnssecDnskeyQueries,
		gtmDnssecZoneStatDnssecNsec3paramQueries,
		gtmDnssecZoneStatDnssecDsQueries,
		gtmDnssecZoneStatSigCryptoFailed,
		gtmDnssecZoneStatSigSuccess,
		gtmDnssecZoneStatSigFailed,
		gtmDnssecZoneStatSigRrsetFailed,
		gtmDnssecZoneStatConnectFlowFailed,
		gtmDnssecZoneStatTowireFailed,
		gtmDnssecZoneStatAxfrQueries,
		gtmDnssecZoneStatIxfrQueries,
		gtmDnssecZoneStatXfrStarts,
		gtmDnssecZoneStatXfrCompletes,
		gtmDnssecZoneStatXfrMsgs,
		gtmDnssecZoneStatXfrMasterMsgs,
		gtmDnssecZoneStatXfrResponseAverageSize,
		gtmDnssecZoneStatXfrSerial,
		gtmDnssecZoneStatXfrMasterSerial,
		gtmDnssecZoneStatDsXfr,
		gtmDnssecZoneStatDsReferral,
		gtmDnssecZoneStatDnssecCdsQueries,
		gtmDnssecZoneStatDnssecCdnskeyQueries
	}
	STATUS	 current
	DESCRIPTION
		"A collection of objects of gtmDnssecZoneStat MIB."
	::= { bigipGlobalTMGroups 50 }

gtmDnssecStatGroup OBJECT-GROUP
	 OBJECTS {
		gtmDnssecStatResetStats,
		gtmDnssecStatNsec3s,
		gtmDnssecStatNsec3Nodata,
		gtmDnssecStatNsec3Nxdomain,
		gtmDnssecStatNsec3Referral,
		gtmDnssecStatNsec3Resalt,
		gtmDnssecStatDnssecResponses,
		gtmDnssecStatDnssecDnskeyQueries,
		gtmDnssecStatDnssecNsec3paramQueries,
		gtmDnssecStatDnssecDsQueries,
		gtmDnssecStatSigCryptoFailed,
		gtmDnssecStatSigSuccess,
		gtmDnssecStatSigFailed,
		gtmDnssecStatSigRrsetFailed,
		gtmDnssecStatConnectFlowFailed,
		gtmDnssecStatTowireFailed,
		gtmDnssecStatAxfrQueries,
		gtmDnssecStatIxfrQueries,
		gtmDnssecStatXfrStarts,
		gtmDnssecStatXfrCompletes,
		gtmDnssecStatXfrMsgs,
		gtmDnssecStatXfrMasterMsgs,
		gtmDnssecStatXfrResponseAverageSize,
		gtmDnssecStatXfrSerial,
		gtmDnssecStatXfrMasterSerial
	}
	STATUS	 current
	DESCRIPTION
		"A collection of objects of gtmGlobalDnssecStat MIB."
	::= { bigipGlobalTMGroups 51 }

gtmApplicationWideipGroup OBJECT-GROUP
	 OBJECTS {
		gtmApplicationWideipNumber,
		gtmApplicationWideipApplicationName,
		gtmApplicationWideipWipName,
		gtmApplicationWideipWipType
	}
	STATUS	 current
	DESCRIPTION
		"A collection of objects of gtmApplicationWideip MIB."
	::= { bigipGlobalTMGroups 52 }

gtmDeviceGroup OBJECT-GROUP
	 OBJECTS {
		gtmDeviceNumber,
		gtmDeviceServerName,
		gtmDeviceName
	}
	STATUS	 current
	DESCRIPTION
		"A collection of objects of gtmDevice MIB."
	::= { bigipGlobalTMGroups 53 }

gtmDeviceStatGroup OBJECT-GROUP
	 OBJECTS {
		gtmDeviceStatResetStats,
		gtmDeviceStatNumber,
		gtmDeviceStatName,
		gtmDeviceStatServerName,
		gtmDeviceStatCpuUsage,
		gtmDeviceStatMemAvail,
		gtmDeviceStatBitsPerSecIn,
		gtmDeviceStatBitsPerSecOut,
		gtmDeviceStatPktsPerSecIn,
		gtmDeviceStatPktsPerSecOut,
		gtmDeviceStatConnections
	}
	STATUS	 current
	DESCRIPTION
		"A collection of objects of gtmDeviceStat MIB."
	::= { bigipGlobalTMGroups 54 }

gtmDeviceStatusGroup OBJECT-GROUP
	 OBJECTS {
		gtmDeviceStatusNumber,
		gtmDeviceStatusName,
		gtmDeviceStatusServerName,
		gtmDeviceStatusAvailState,
		gtmDeviceStatusEnabledState,
		gtmDeviceStatusDetailReason
	}
	STATUS	 current
	DESCRIPTION
		"A collection of objects of gtmDeviceStatus MIB."
	::= { bigipGlobalTMGroups 55 }

gtmDeviceIpGroup OBJECT-GROUP
	 OBJECTS {
		gtmDeviceIpNumber,
		gtmDeviceIpServerName,
		gtmDeviceIpDeviceName,
		gtmDeviceIpIpType,
		gtmDeviceIpIp,
		gtmDeviceIpIpXlatedType,
		gtmDeviceIpIpXlated
	}
	STATUS	 current
	DESCRIPTION
		"A collection of objects of gtmDeviceIp MIB."
	::= { bigipGlobalTMGroups 56 }

gtmLinkIpGroup OBJECT-GROUP
	 OBJECTS {
		gtmLinkIpNumber,
		gtmLinkIpLinkName,
		gtmLinkIpIpType,
		gtmLinkIpIp,
		gtmLinkIpIpXlatedType,
		gtmLinkIpIpXlated
	}
	STATUS	 current
	DESCRIPTION
		"A collection of objects of gtmLinkIp MIB."
	::= { bigipGlobalTMGroups 57 }
END
