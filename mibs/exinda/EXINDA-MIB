EXINDA-MIB DEFINITIONS ::= BEGIN

--
--  (C) Copyright 2009 Exinda Networks Pty Ltd
--  All rights reserved.
--

IMPORTS
   OBJECT-TYPE, MODULE-IDENTITY, NOTIFICATION-TYPE, enterprises, Counter32, Gauge32, Counter64, Integer32, Unsigned32, TimeTicks
      FROM SNMPv2-SMI
   TruthValue
      FROM SNMPv2-TC;

exinda MODULE-IDENTITY
   LAST-UPDATED  "200908281359Z"
   ORGANIZATION  "Exinda Networks Pty Ltd"
   CONTACT-INFO  "support@exinda.com"

   DESCRIPTION   "Exinda Networks Vendor MIB"

   REVISION      "200908281359Z"
   DESCRIPTION   "Revision V5.3.0"

   ::= { enterprises 21091 }

--
-- System
--

system OBJECT IDENTIFIER
   ::= { exinda 1 }

systemInfo OBJECT IDENTIFIER
   ::= { system 1 }

hardwareSeries OBJECT-TYPE
   SYNTAX      OCTET STRING
   MAX-ACCESS  read-only
   STATUS      current
   DESCRIPTION "Hardware series"
   ::= { systemInfo 1 }

licensedModel OBJECT-TYPE
   SYNTAX      OCTET STRING
   MAX-ACCESS  read-only
   STATUS      current
   DESCRIPTION "Licensed model"
   ::= { systemInfo 2 }

systemVersion OBJECT-TYPE
   SYNTAX      OCTET STRING
   MAX-ACCESS  read-only
   STATUS      current
   DESCRIPTION "System ExOS version"
   ::= { systemInfo 3 }

systemHostId OBJECT-TYPE
   SYNTAX      OCTET STRING
   MAX-ACCESS  read-only
   STATUS      current
   DESCRIPTION "System Host ID"
   ::= { systemInfo 4 }

systemUptime OBJECT-TYPE
   SYNTAX      TimeTicks
   MAX-ACCESS  read-only
   STATUS      current
   DESCRIPTION "System uptime in milliseconds"
   ::= { systemInfo 5 }

configName OBJECT-TYPE
   SYNTAX      OCTET STRING
   MAX-ACCESS  read-only
   STATUS      current
   DESCRIPTION "Current configuration database name"
   ::= { systemInfo 6 }

configUnsavedChanges OBJECT-TYPE
   SYNTAX      Integer32
   MAX-ACCESS  read-only
   STATUS      current
   DESCRIPTION "Unsaved configuration changes {Unsaved(1), Saved(2)}"
   ::= { systemInfo 7 }

systemTimeZone OBJECT-TYPE
   SYNTAX      OCTET STRING
   MAX-ACCESS  read-only
   STATUS      current
   DESCRIPTION "System timezone"
   ::= { systemInfo 8 }

cpu OBJECT IDENTIFIER
    ::= { system 2 }

cpuLoad1 OBJECT-TYPE
    SYNTAX      Unsigned32
    MAX-ACCESS  read-only
    STATUS      current
    DESCRIPTION "One-minute CPU load in hundreths"
    ::= { cpu 1 }

cpuLoad5 OBJECT-TYPE
    SYNTAX      Unsigned32
    MAX-ACCESS  read-only
    STATUS      current
    DESCRIPTION "Five-minute CPU load in hundreths"
    ::= { cpu 2 }

cpuLoad15 OBJECT-TYPE
    SYNTAX      Unsigned32
    MAX-ACCESS  read-only
    STATUS      current
    DESCRIPTION "Fifteen-minute CPU load in hundreths"
    ::= { cpu 3 }

cpuUsagePercent OBJECT-TYPE
    SYNTAX      Unsigned32
    MAX-ACCESS  read-only
    STATUS      current
    DESCRIPTION "Percentage CPU utilization for all CPUs over the past minute"
    ::= { cpu 4 }

cpuTemperature OBJECT-TYPE
    SYNTAX      Unsigned32
    MAX-ACCESS  read-only
    STATUS      current
    DESCRIPTION "Current CPU temperature"
    ::= { cpu 5 }

ram OBJECT IDENTIFIER
    ::= { system 3 }

totalRam OBJECT-TYPE
    SYNTAX      Unsigned32
    MAX-ACCESS  read-only
    STATUS      current
    DESCRIPTION "Total physical system RAM in kbytes"
    ::= { ram 1 }

usedRam OBJECT-TYPE
    SYNTAX      Unsigned32
    MAX-ACCESS  read-only
    STATUS      current
    DESCRIPTION "Used physical system RAM in kbytes"
    ::= { ram 2 }

freeRam OBJECT-TYPE
    SYNTAX      Unsigned32
    MAX-ACCESS  read-only
    STATUS      current
    DESCRIPTION "Free physical system RAM in kbytes"
    ::= { ram 3 }

systemHealth OBJECT IDENTIFIER
    ::= { system 4 }

cpuAlarm OBJECT-TYPE
   SYNTAX OCTET STRING
   MAX-ACCESS  read-only
   STATUS      deprecated
   DESCRIPTION "High CPU utilization"
   ::= { systemHealth 1 }

ramAlarm OBJECT-TYPE
   SYNTAX OCTET STRING
   MAX-ACCESS  read-only
   STATUS      deprecated
   DESCRIPTION "High swap utilization"
   ::= { systemHealth 2 }

diskAlarm OBJECT-TYPE
   SYNTAX OCTET STRING
   MAX-ACCESS  read-only
   STATUS      deprecated
   DESCRIPTION "Full (or almost full) disk partition"
   ::= { systemHealth 3 }

nicAlarm OBJECT-TYPE
   SYNTAX OCTET STRING
   MAX-ACCESS  read-only
   STATUS      deprecated
   DESCRIPTION "High collision rate on NICs"
   ::= { systemHealth 4 }

license OBJECT IDENTIFIER
    ::= { system 5 }

licensed OBJECT-TYPE
    SYNTAX      INTEGER {false(0), true(1)}
    MAX-ACCESS  read-only
    STATUS      current
    DESCRIPTION "System licensed"
    ::= { license 1 }

ssExpiry OBJECT-TYPE
    SYNTAX      OCTET STRING
    MAX-ACCESS  read-only
    STATUS      current
    DESCRIPTION "Expiry date for software subscription"
    ::= { license 2 }

maxBandwidth OBJECT-TYPE
    SYNTAX      Unsigned32
    MAX-ACCESS  read-only
    STATUS      current
    DESCRIPTION "Licensed maximum bandwidth"
    ::= { license 3 }

maxConnections OBJECT-TYPE
    SYNTAX      Unsigned32
    MAX-ACCESS  read-only
    STATUS      current
    DESCRIPTION "Licensed maximum connections"
    ::= { license 4 }

maxConnectionRate OBJECT-TYPE
    SYNTAX      Unsigned32
    MAX-ACCESS  read-only
    STATUS      current
    DESCRIPTION "Licensed maximum connection rate"
    ::= { license 5 }

maxAccelerationBandwidth OBJECT-TYPE
    SYNTAX      Unsigned32
    MAX-ACCESS  read-only
    STATUS      current
    DESCRIPTION "Licensed bandwidth for acceleration"
    ::= { license 6 }

maxAccelerationConnections OBJECT-TYPE
    SYNTAX      Unsigned32
    MAX-ACCESS  read-only
    STATUS      current
    DESCRIPTION "Licensed connections for acceleration"
    ::= { license 7 }

hardwareAssistedL7 OBJECT-TYPE
    SYNTAX      OCTET STRING
    MAX-ACCESS  read-only
    STATUS      deprecated
    DESCRIPTION "Licenced for fast L7 inspection (monitoring) (Deprecated)"
    ::= { license 8 }

optimizerLicensedDepr OBJECT-TYPE
    SYNTAX      OCTET STRING
    MAX-ACCESS  read-only
    STATUS      deprecated
    DESCRIPTION "Licenced for optimizer (Deprecated)"
    ::= { license 9 }

maxOptimizerPolicies OBJECT-TYPE
    SYNTAX      Unsigned32
    MAX-ACCESS  read-only
    STATUS      current
    DESCRIPTION "Licensed maximum number of optimizer policies"
    ::= { license 10 }

maxApsObjects OBJECT-TYPE
    SYNTAX      Unsigned32
    MAX-ACCESS  read-only
    STATUS      current
    DESCRIPTION "Licensed maximum number of APS monitoring objects"
    ::= { license 11 }

maxSlaObjects OBJECT-TYPE
    SYNTAX      Unsigned32
    MAX-ACCESS  read-only
    STATUS      current
    DESCRIPTION "Licensed maximum number of SLA monitoring objects"
    ::= { license 12 }

maxPdfReports OBJECT-TYPE
    SYNTAX      Unsigned32
    MAX-ACCESS  read-only
    STATUS      current
    DESCRIPTION "Licensed maximum number of PDF Reports"
    ::= { license 13 }

sslAccelerationLicensedDepr OBJECT-TYPE
    SYNTAX      Unsigned32
    MAX-ACCESS  read-only
    STATUS      deprecated
    DESCRIPTION "Licensed for SSL Acceleration (Deprecated)"
    ::= { license 14 }

virtualizationLicensedDepr OBJECT-TYPE
    SYNTAX      OCTET STRING
    MAX-ACCESS  read-only
    STATUS      deprecated
    DESCRIPTION "Licensed for Virtualization (Deprecated)"
    ::= { license 15 }

webCacheLicensedDepr OBJECT-TYPE
    SYNTAX      OCTET STRING
    MAX-ACCESS  read-only
    STATUS      deprecated
    DESCRIPTION "Licensed Web Caching (Deprecated)"
    ::= { license 16 }

maxApmObjects OBJECT-TYPE
    SYNTAX      Unsigned32
    MAX-ACCESS  read-only
    STATUS      current
    DESCRIPTION "Licensed maximum number of APM monitoring objects"
    ::= { license 17 }

sslAccelerationLicensed OBJECT-TYPE
    SYNTAX      INTEGER {false(0), true(1)}
    MAX-ACCESS  read-only
    STATUS      current
    DESCRIPTION "Licensed for SSL Acceleration"
    ::= { license 18 }

virtualizationLicensed OBJECT-TYPE
    SYNTAX      INTEGER {false(0), true(1)}
    MAX-ACCESS  read-only
    STATUS      current
    DESCRIPTION "Licensed for Virtualization"
    ::= { license 19 }

webCacheLicensed OBJECT-TYPE
    SYNTAX      INTEGER {false(0), true(1)}
    MAX-ACCESS  read-only
    STATUS      current
    DESCRIPTION "Licensed Web Caching"
    ::= { license 20 }

optimizerLicensed OBJECT-TYPE
    SYNTAX      INTEGER {false(0), true(1)}
    MAX-ACCESS  read-only
    STATUS      current
    DESCRIPTION "Licenced for optimizer"
    ::= { license 21 }

maxNumOfEdgeCacheConnection OBJECT-TYPE
    SYNTAX      Unsigned32
    MAX-ACCESS  read-only
    STATUS      current
    DESCRIPTION "Maximum numver of Edge-cache connection"
    ::= { license 22 }

processes OBJECT IDENTIFIER
    ::= { system 6 }

procTable OBJECT-TYPE
    SYNTAX      SEQUENCE OF ProcEntrySeq
    MAX-ACCESS  not-accessible
    STATUS      current
    DESCRIPTION "List of processes managed or monitored by PM"
    ::= { processes 1 }

procEntry OBJECT-TYPE
    SYNTAX      ProcEntrySeq
    MAX-ACCESS  not-accessible
    STATUS      current
    DESCRIPTION "Entry for one process"
    INDEX   { procIndex }
    ::= { procTable 1 }

ProcEntrySeq ::=
    SEQUENCE {
        procIndex            Unsigned32,
        procName             OCTET STRING,
        procStatus           OCTET STRING,
        procNumFailures      Unsigned32
    }

procIndex OBJECT-TYPE
    SYNTAX      Unsigned32
    MAX-ACCESS  read-only
    STATUS      current
    DESCRIPTION "Synthetic numeric unique ID of process"
    ::= { procEntry 1 }

procName OBJECT-TYPE
    SYNTAX      OCTET STRING
    MAX-ACCESS  read-only
    STATUS      current
    DESCRIPTION "Unique name of process"
    ::= { procEntry 2 }

procStatus OBJECT-TYPE
    SYNTAX      OCTET STRING
    MAX-ACCESS  read-only
    STATUS      current
    DESCRIPTION "Current state of process"
    ::= { procEntry 3 }

procNumFailures OBJECT-TYPE
    SYNTAX      Unsigned32
    MAX-ACCESS  read-only
    STATUS      current
    DESCRIPTION "Number of times process has crashed or exited unexpectedly"
    ::= { procEntry 4 }

--
-- Monitor
--

monitor OBJECT IDENTIFIER
    ::= { exinda 2 }

collectorStatus OBJECT-TYPE
    SYNTAX      Integer32
    MAX-ACCESS  read-only
    STATUS      current
    DESCRIPTION "Collector state code {Unknown(0), OK(1), Starting(2), Stopping(3), Error(4)} "
    ::= { monitor 1 }

-- armStatus OBJECT-TYPE
--     SYNTAX      TruthValue
--     MAX-ACCESS  read-only
--     STATUS      current
--     DESCRIPTION "ARM enabled"
--     ::= { monitor 2 }

--
-- Optimizer
--

optimizer OBJECT IDENTIFIER
    ::= { exinda 3 }

optimizerState OBJECT-TYPE
    SYNTAX      Unsigned32
    MAX-ACCESS  read-only
    STATUS      current
    DESCRIPTION "Optimizer state code"
    ::= { optimizer 1 }

optimizerRestartRequired OBJECT-TYPE
    SYNTAX      TruthValue
    MAX-ACCESS  read-only
    STATUS      current
    DESCRIPTION "Optimizer restart required for changes to take affect"
    ::= { optimizer 2 }

optimizerTable OBJECT-TYPE
    SYNTAX      SEQUENCE OF OptimizerEntrySeq
    MAX-ACCESS  not-accessible
    STATUS      current
    DESCRIPTION "List of optimizer policies"
    ::= { optimizer 3 }

optimizerEntry OBJECT-TYPE
    SYNTAX      OptimizerEntrySeq
    MAX-ACCESS  not-accessible
    STATUS      current
    DESCRIPTION "Entry for one optimizer policy"
    INDEX       { optimizerIndex }
    ::= { optimizerTable 1 }

OptimizerEntrySeq ::=
    SEQUENCE {
        optimizerIndex               Unsigned32,
        optimizerId                  OCTET STRING,
        optimizerCircuit             OCTET STRING,
        optimizerVcircuit            OCTET STRING,
        optimizerPolicy              OCTET STRING,
        optimizerDirection           OCTET STRING,
        optimizerGuaranteedBandwidth Unsigned32,
        optimizerMaximumBandwidth    Unsigned32,
        optimizerCurrentRate         Unsigned32,
        optimizerOctets              Counter64,
        optimizerBytes               OCTET STRING
    }

optimizerIndex OBJECT-TYPE
    SYNTAX      Unsigned32
    MAX-ACCESS  read-only
    STATUS      current
    DESCRIPTION "Synthetic numeric unique ID of optimizer policy"
    ::= { optimizerEntry 1 }

optimizerId OBJECT-TYPE
    SYNTAX      OCTET STRING
    MAX-ACCESS  read-only
    STATUS      current
    DESCRIPTION "ID of optimizer policy"
    ::= { optimizerEntry 2 }

optimizerCircuit OBJECT-TYPE
    SYNTAX      OCTET STRING
    MAX-ACCESS  read-only
    STATUS      current
    DESCRIPTION "Circuit name of optimizer policy"
    ::= { optimizerEntry 3 }

optimizerVcircuit OBJECT-TYPE
    SYNTAX      OCTET STRING
    MAX-ACCESS  read-only
    STATUS      current
    DESCRIPTION "Virtual Circuit name of optimizer policy"
    ::= { optimizerEntry 4 }

optimizerPolicy OBJECT-TYPE
    SYNTAX      OCTET STRING
    MAX-ACCESS  read-only
    STATUS      current
    DESCRIPTION "Policy name"
    ::= { optimizerEntry 5 }

optimizerDirection OBJECT-TYPE
    SYNTAX      OCTET STRING
    MAX-ACCESS  read-only
    STATUS      current
    DESCRIPTION "Direction of optimizer policy"
    ::= { optimizerEntry 6 }

optimizerGuaranteedBandwidth OBJECT-TYPE
    SYNTAX      Unsigned32
    MAX-ACCESS  read-only
    STATUS      current
    DESCRIPTION "Guaranteed rate (kbps) through optimizer policy"
    ::= { optimizerEntry 7 }

optimizerMaximumBandwidth OBJECT-TYPE
    SYNTAX      Unsigned32
    MAX-ACCESS  read-only
    STATUS      current
    DESCRIPTION "Maximum rate (kbps) allowed through optimizer policy"
    ::= { optimizerEntry 8 }

optimizerCurrentRate OBJECT-TYPE
    SYNTAX      Unsigned32
    MAX-ACCESS  read-only
    STATUS      current
    DESCRIPTION "Current rate (kbps) through optimizer policy"
    ::= { optimizerEntry 9 }

optimizerOctets OBJECT-TYPE
    SYNTAX      Counter64
    MAX-ACCESS  read-only
    STATUS      current
    DESCRIPTION "Octets transferred through optimizer policy"
    ::= { optimizerEntry 10 }

optimizerBytes OBJECT-TYPE
    SYNTAX      OCTET STRING
    MAX-ACCESS  read-only
    STATUS      current
    DESCRIPTION "Bytes transferred through optimizer policy"
    ::= { optimizerEntry 11 }

--
-- Acceleration
--

acceleration OBJECT IDENTIFIER
    ::= { exinda 4 }

exindaCommunity OBJECT IDENTIFIER
    ::= { acceleration 1 }

communityState OBJECT-TYPE
    SYNTAX      OCTET STRING
    MAX-ACCESS  read-only
    STATUS      current
    DESCRIPTION "Exinda Community status"
    ::= { exindaCommunity 1 }

communityTable OBJECT-TYPE
    SYNTAX      SEQUENCE OF CommunityPeerEntrySeq
    MAX-ACCESS  not-accessible
    STATUS      current
    DESCRIPTION "List of peers in the community"
    ::= { exindaCommunity 2 }

communityPeerEntry OBJECT-TYPE
    SYNTAX      CommunityPeerEntrySeq
    MAX-ACCESS  not-accessible
    STATUS      current
    DESCRIPTION "Entry for one community peer"
    INDEX       { communityPeerIndex }
    ::= { communityTable 1 }

CommunityPeerEntrySeq ::=
    SEQUENCE {
        communityPeerIndex       Unsigned32,
        communityPeerHostId      OCTET STRING,
        communityPeerHostname    OCTET STRING,
        communityPeerVersion     OCTET STRING,
        communityPeerState       OCTET STRING
    }

communityPeerIndex OBJECT-TYPE
    SYNTAX      Unsigned32
    MAX-ACCESS  read-only
    STATUS      current
    DESCRIPTION "Synthetic numeric unique ID of community peer"
    ::= { communityPeerEntry 1 }

communityPeerHostId OBJECT-TYPE
    SYNTAX      OCTET STRING
    MAX-ACCESS  read-only
    STATUS      current
    DESCRIPTION "Host ID of community peer"
    ::= { communityPeerEntry 2 }

communityPeerHostname OBJECT-TYPE
    SYNTAX      OCTET STRING
    MAX-ACCESS  read-only
    STATUS      current
    DESCRIPTION "Hostname of community peer"
    ::= { communityPeerEntry 3 }

communityPeerVersion OBJECT-TYPE
    SYNTAX      OCTET STRING
    MAX-ACCESS  read-only
    STATUS      current
    DESCRIPTION "ExOS version of community peer"
    ::= { communityPeerEntry 4 }

communityPeerState OBJECT-TYPE
    SYNTAX      OCTET STRING
    MAX-ACCESS  read-only
    STATUS      current
    DESCRIPTION "State of community peer"
    ::= { communityPeerEntry 5 }

tcpAcceleration OBJECT IDENTIFIER
    ::= { acceleration 2 }

tcpaCongestionControl OBJECT-TYPE
    SYNTAX      OCTET STRING
    MAX-ACCESS  read-only
    STATUS      current
    DESCRIPTION "TCPA congestion control"
    ::= { tcpAcceleration 1 }

tcpaTransportMode OBJECT-TYPE
    SYNTAX      OCTET STRING
    MAX-ACCESS  read-only
    STATUS      current
    DESCRIPTION "TCPA transport mode"
    ::= { tcpAcceleration 2 }

-- tcpaWindowSize OBJECT-TYPE
--     SYNTAX      Unsigned32
--     MAX-ACCESS  read-only
--     STATUS      current
--     DESCRIPTION "TCPA window size in kbytes"
--     ::= { tcpAcceleration 3 }

-- tcpaMtu OBJECT-TYPE
--     SYNTAX      Unsigned32
--     MAX-ACCESS  read-only
--     STATUS      current
--     DESCRIPTION "TCPA MTU in bytes"
--     ::= { tcpAcceleration 4 }

tcpaConnectionsCurrent OBJECT-TYPE
    SYNTAX      Unsigned32
    MAX-ACCESS  read-only
    STATUS      current
    DESCRIPTION "The number of concurrent connections being accelerated"
    ::= { tcpAcceleration 5 }

-- tcpaConnectionsTotal OBJECT-TYPE
--     SYNTAX      Unsigned32
--     MAX-ACCESS  read-only
--     STATUS      current
--     DESCRIPTION "Total number of TCP Accelerated connections"
--     ::= { tcpAcceleration 6 }

tcpaConnectionsPeak OBJECT-TYPE
    SYNTAX      Unsigned32
    MAX-ACCESS  read-only
    STATUS      current
    DESCRIPTION "The maximum number of concurrent connections being accelerated at any one time"
    ::= { tcpAcceleration 7 }

-- tcpaTable OBJECT-TYPE
--     SYNTAX      SEQUENCE OF tcpaPeerEntrySeq
--     MAX-ACCESS  not-accessible
--     STATUS      current
--     DESCRIPTION "List of TCP Acceleration peers"
--     ::= { tcpAcceleration 8 }

tcpaConnectionsNew OBJECT-TYPE
    SYNTAX      Unsigned32
    MAX-ACCESS  read-only
    STATUS      current
    DESCRIPTION "The average new accelerated connections per second"
    ::= { tcpAcceleration 9 }

tcpaDiscovery OBJECT-TYPE
    SYNTAX      TruthValue
    MAX-ACCESS  read-only
    STATUS      current
    DESCRIPTION "Appliance discovery is enabled"
    ::= { tcpAcceleration 10 }

tcpaDiscoveryAddr OBJECT-TYPE
    SYNTAX      IpAddress
    MAX-ACCESS  read-only
    STATUS      current
    DESCRIPTION "Override the IP address that is used for appliance discovery"
    ::= { tcpAcceleration 11 }

tcpaDualBridgeBypass OBJECT-TYPE
    SYNTAX      TruthValue
    MAX-ACCESS  read-only
    STATUS      current
    DESCRIPTION "Dual bridge acceleration bypass is enabled"
    ::= { tcpAcceleration 12 }

tcpaWindowScale OBJECT-TYPE
    SYNTAX      Unsigned32
    MAX-ACCESS  read-only
    STATUS      current
    DESCRIPTION "The TCP window scaling factor"
    ::= { tcpAcceleration 13 }

-- tcpaPeerEntry OBJECT-TYPE
--     SYNTAX      tcpaPeerEntrySeq
--     MAX-ACCESS  not-accessible
--     STATUS      current
--     DESCRIPTION "Entry for one TCP Acceleration peer"
--     INDEX   { tcpaPeerIndex }
--     ::= { tcpaTable 1 }

-- tcpaPeerEntrySeq ::=
--     SEQUENCE {
--         tcpaPeerIndex                 Unsigned32,
--         tcpaPeerHostId                OCTET STRING,
--         tcpaPeerIp                    IpAddress,
--         tcpaPeerHosts                 Unsigned32,
--        tcpaPeerRtt                   TimeTicks
--     }

-- tcpaPeerIndex OBJECT-TYPE
--     SYNTAX      Unsigned32
--     MAX-ACCESS  read-only
--     STATUS      current
--     DESCRIPTION "Synthetic numeric unique ID of TCP Acceleration peer"
--     ::= { tcpaPeerEntry 1 }

-- tcpaPeerHostId OBJECT-TYPE
--     SYNTAX      OCTET STRING
--     MAX-ACCESS  read-only
--     STATUS      current
--     DESCRIPTION "Host ID of TCP Acceleration peer"
--     ::= { tcpaPeerEntry 2 }

-- tcpaPeerIp OBJECT-TYPE
--     SYNTAX      IpAddress
--     MAX-ACCESS  read-only
--     STATUS      current
--     DESCRIPTION "IP address of TCP Acceleration peer"
--     ::= { tcpaPeerEntry 3 }

-- tcpaPeerHosts OBJECT-TYPE
--     SYNTAX      OCTET STRING
--     MAX-ACCESS  read-only
--     STATUS      current
--     DESCRIPTION "Number of discovered hosts behind TCP Acceleration peer"
--     ::= { tcpaPeerEntry 4 }

-- tcpaPeerRtt OBJECT-TYPE
--     SYNTAX      TimeTicks
--     MAX-ACCESS  read-only
--     STATUS      current
--     DESCRIPTION "Average RTT of TCP Acceleration peer"
--     ::= { tcpaPeerEntry 5 }


wanMemory OBJECT IDENTIFIER
    ::= { acceleration 3 }

wmCompression OBJECT-TYPE
    SYNTAX      TruthValue
    MAX-ACCESS  read-only
    STATUS      current
    DESCRIPTION "WAN Memory compression enabled"
    ::= { wanMemory 1 }

wmSmallMatcher OBJECT-TYPE
    SYNTAX      TruthValue
    MAX-ACCESS  read-only
    STATUS      current
    DESCRIPTION "WAN Memory small matching enabled"
    ::= { wanMemory 2 }

wmPersistence OBJECT-TYPE
    SYNTAX      TruthValue
    MAX-ACCESS  read-only
    STATUS      current
    DESCRIPTION "WAN Memory persistence enabled"
    ::= { wanMemory 3 }

wmDiskSize OBJECT-TYPE
    SYNTAX      Counter64
    MAX-ACCESS  read-only
    STATUS      current
    DESCRIPTION "WAN Memory total disk storage (bytes)"
    ::= { wanMemory 4 }

wmDiskUsed OBJECT-TYPE
    SYNTAX      Counter64
    MAX-ACCESS  read-only
    STATUS      current
    DESCRIPTION "WAN Memory disk storage used (bytes)"
    ::= { wanMemory 5 }

wmDiskUsedPercent OBJECT-TYPE
    SYNTAX      OCTET STRING
    MAX-ACCESS  read-only
    STATUS      current
    DESCRIPTION "WAN Memory disk storage used (percent)"
    ::= { wanMemory 6 }

wmSendBytesIn OBJECT-TYPE
    SYNTAX      Counter64
    MAX-ACCESS  read-only
    STATUS      current
    DESCRIPTION "WAN Memory TX bytes in"
    ::= { wanMemory 7 }

wmSendBytesOut OBJECT-TYPE
    SYNTAX      Counter64
    MAX-ACCESS  read-only
    STATUS      current
    DESCRIPTION "WAN Memory TX bytes out"
    ::= { wanMemory 8 }

wmSendReductionPercent OBJECT-TYPE
    SYNTAX      OCTET STRING
    MAX-ACCESS  read-only
    STATUS      current
    DESCRIPTION "WAN Memory TX reduction percentage"
    ::= { wanMemory 9 }

wmReceiveBytesIn OBJECT-TYPE
    SYNTAX      Counter64
    MAX-ACCESS  read-only
    STATUS      current
    DESCRIPTION "WAN Memory RX bytes in"
    ::= { wanMemory 10 }

wmReceiveBytesOut OBJECT-TYPE
    SYNTAX      Counter64
    MAX-ACCESS  read-only
    STATUS      current
    DESCRIPTION "WAN Memory RX bytes out"
    ::= { wanMemory 11 }

wmReceiveReductionPercent OBJECT-TYPE
    SYNTAX      OCTET STRING
    MAX-ACCESS  read-only
    STATUS      current
    DESCRIPTION "WAN Memory RX reduction percentage"
    ::= { wanMemory 12 }

wmTable OBJECT-TYPE
    SYNTAX      SEQUENCE OF WmPeerEntrySeq
    MAX-ACCESS  not-accessible
    STATUS      current
    DESCRIPTION "List of WAN Memory peers"
    ::= { wanMemory 13 }

wmPeerEntry OBJECT-TYPE
    SYNTAX      WmPeerEntrySeq
    MAX-ACCESS  not-accessible
    STATUS      current
    DESCRIPTION "Entry for one WAN Memory peer"
    INDEX   { wmPeerIndex }
    ::= { wmTable 1 }

WmPeerEntrySeq ::=
    SEQUENCE {
        wmPeerIndex                   Unsigned32,
        wmPeerHostId                  OCTET STRING,
        wmPeerIp                      IpAddress,
        wmPeerStatus                  OCTET STRING,
        wmPeerDiskStatus              OCTET STRING,
        wmPeerConnections             Unsigned32,
        wmPeerSendReductionPercent    OCTET STRING,
        wmPeerReceiveReductionPercent OCTET STRING
    }

wmPeerIndex OBJECT-TYPE
    SYNTAX      Unsigned32
    MAX-ACCESS  read-only
    STATUS      current
    DESCRIPTION "Synthetic numeric unique ID of WAN Memory peer"
    ::= { wmPeerEntry 1 }

wmPeerHostId OBJECT-TYPE
    SYNTAX      OCTET STRING
    MAX-ACCESS  read-only
    STATUS      current
    DESCRIPTION "Host ID of WAN Memory peer"
    ::= { wmPeerEntry 2 }

wmPeerIp OBJECT-TYPE
    SYNTAX      IpAddress
    MAX-ACCESS  read-only
    STATUS      current
    DESCRIPTION "IP address of WAN Memory peer"
    ::= { wmPeerEntry 3 }

wmPeerStatus OBJECT-TYPE
    SYNTAX      OCTET STRING
    MAX-ACCESS  read-only
    STATUS      current
    DESCRIPTION "Status of WAN Memory peer"
    ::= { wmPeerEntry 4 }

wmPeerDiskStatus OBJECT-TYPE
    SYNTAX      OCTET STRING
    MAX-ACCESS  read-only
    STATUS      current
    DESCRIPTION "Disk status of WAN Memory peer"
    ::= { wmPeerEntry 5 }

wmPeerConnections OBJECT-TYPE
    SYNTAX      Unsigned32
    MAX-ACCESS  read-only
    STATUS      current
    DESCRIPTION "Number of connections through WAN Memory peer"
    ::= { wmPeerEntry 6 }

wmPeerSendReductionPercent OBJECT-TYPE
    SYNTAX      OCTET STRING
    MAX-ACCESS  read-only
    STATUS      current
    DESCRIPTION "TX reduction percentage for WAN Memory peer"
    ::= { wmPeerEntry 7 }

wmPeerReceiveReductionPercent OBJECT-TYPE
    SYNTAX      OCTET STRING
    MAX-ACCESS  read-only
    STATUS      current
    DESCRIPTION "RX reduction percentage for WAN Memory peer"
    ::= { wmPeerEntry 8 }

cifsAcceleration OBJECT IDENTIFIER
    ::= { acceleration 4 }

cifsEnabled OBJECT-TYPE
    SYNTAX      TruthValue
    MAX-ACCESS  read-only
    STATUS      current
    DESCRIPTION "CIFS acceleration enabled"
    ::= { cifsAcceleration 1 }

cifsReadAhead OBJECT-TYPE
    SYNTAX      TruthValue
    MAX-ACCESS  read-only
    STATUS      current
    DESCRIPTION "CIFS read-ahead acceleration read-ahead enabled"
    ::= { cifsAcceleration 2 }

cifsWriteAhead OBJECT-TYPE
    SYNTAX      TruthValue
    MAX-ACCESS  read-only
    STATUS      current
    DESCRIPTION "CIFS write-ahead acceleration read-ahead enabled"
    ::= { cifsAcceleration 3 }

cifsTransactionAcceleration OBJECT-TYPE
    SYNTAX      TruthValue
    MAX-ACCESS  read-only
    STATUS      current
    DESCRIPTION "CIFS transaction acceleration enabled"
    ::= { cifsAcceleration 4 }

cifsConcurrentConnections OBJECT-TYPE
    SYNTAX      Unsigned32
    MAX-ACCESS  read-only
    STATUS      current
    DESCRIPTION "Current number of CIFS connections"
    ::= { cifsAcceleration 5 }

cifsConcurrentAcceleratedConnections OBJECT-TYPE
    SYNTAX      Unsigned32
    MAX-ACCESS  read-only
    STATUS      current
    DESCRIPTION "Current number of CIFS accelerated connections"
    ::= { cifsAcceleration 6 }

cifsConcurrentSignedConnections OBJECT-TYPE
    SYNTAX      Unsigned32
    MAX-ACCESS  read-only
    STATUS      current
    DESCRIPTION "Current number of CIFS signed connections"
    ::= { cifsAcceleration 7 }

wanMemoryNew OBJECT IDENTIFIER
    ::= { acceleration 5 }

wmCompression OBJECT-TYPE
    SYNTAX      TruthValue
    MAX-ACCESS  read-only
    STATUS      current
    DESCRIPTION "WAN Memory compression enabled"
    ::= { wanMemoryNew 1 }

wmSmallMatcher OBJECT-TYPE
    SYNTAX      TruthValue
    MAX-ACCESS  read-only
    STATUS      current
    DESCRIPTION "WAN Memory small matching enabled"
    ::= { wanMemoryNew 2 }

wmPersistence OBJECT-TYPE
    SYNTAX      TruthValue
    MAX-ACCESS  read-only
    STATUS      current
    DESCRIPTION "WAN Memory persistence enabled"
    ::= { wanMemoryNew 3 }

wmDiskSize OBJECT-TYPE
    SYNTAX      OCTET STRING
    MAX-ACCESS  read-only
    STATUS      current
    DESCRIPTION "WAN Memory total disk storage (bytes)"
    ::= { wanMemoryNew 4 }

wmDiskUsed OBJECT-TYPE
    SYNTAX      OCTET STRING
    MAX-ACCESS  read-only
    STATUS      current
    DESCRIPTION "WAN Memory disk storage used (bytes)"
    ::= { wanMemoryNew 5 }

wmDiskUsedPercent OBJECT-TYPE
    SYNTAX      OCTET STRING
    MAX-ACCESS  read-only
    STATUS      current
    DESCRIPTION "WAN Memory disk storage used (percent)"
    ::= { wanMemoryNew 6 }

wmSendBytesIn OBJECT-TYPE
    SYNTAX      OCTET STRING
    MAX-ACCESS  read-only
    STATUS      current
    DESCRIPTION "WAN Memory TX bytes in"
    ::= { wanMemoryNew 7 }

wmSendBytesOut OBJECT-TYPE
    SYNTAX      OCTET STRING
    MAX-ACCESS  read-only
    STATUS      current
    DESCRIPTION "WAN Memory TX bytes out"
    ::= { wanMemoryNew 8 }

wmSendReductionPercent OBJECT-TYPE
    SYNTAX      OCTET STRING
    MAX-ACCESS  read-only
    STATUS      current
    DESCRIPTION "WAN Memory TX reduction percentage"
    ::= { wanMemoryNew 9 }

wmReceiveBytesIn OBJECT-TYPE
    SYNTAX      OCTET STRING
    MAX-ACCESS  read-only
    STATUS      current
    DESCRIPTION "WAN Memory RX bytes in"
    ::= { wanMemoryNew 10 }

wmReceiveBytesOut OBJECT-TYPE
    SYNTAX      OCTET STRING
    MAX-ACCESS  read-only
    STATUS      current
    DESCRIPTION "WAN Memory RX bytes out"
    ::= { wanMemoryNew 11 }

wmReceiveReductionPercent OBJECT-TYPE
    SYNTAX      OCTET STRING
    MAX-ACCESS  read-only
    STATUS      current
    DESCRIPTION "WAN Memory RX reduction percentage"
    ::= { wanMemoryNew 12 }

wmTable OBJECT-TYPE
    SYNTAX      SEQUENCE OF WmPeerEntrySeqNew
    MAX-ACCESS  not-accessible
    STATUS      current
    DESCRIPTION "List of WAN Memory peers"
    ::= { wanMemoryNew 13 }

wmPeerEntryNew OBJECT-TYPE
    SYNTAX      WmPeerEntrySeqNew
    MAX-ACCESS  not-accessible
    STATUS      current
    DESCRIPTION "Entry for one WAN Memory peer"
    INDEX   { wmPeerIndexNew }
    ::= { wmTable 1 }

WmPeerEntrySeqNew ::=
    SEQUENCE {
        wmPeerIndex                   Unsigned32,
        wmPeerHostId                  OCTET STRING,
        wmPeerIp                      IpAddress,
        wmPeerStatus                  OCTET STRING,
        wmPeerDiskStatus              OCTET STRING,
        wmPeerConnections             Unsigned32,
        wmPeerSendReductionPercent    OCTET STRING,
        wmPeerReceiveReductionPercent OCTET STRING
    }

wmPeerIndexNew OBJECT-TYPE
    SYNTAX      Unsigned32
    MAX-ACCESS  read-only
    STATUS      current
    DESCRIPTION "Synthetic numeric unique ID of WAN Memory peer"
    ::= { wmPeerEntryNew 1 }

wmPeerHostId OBJECT-TYPE
    SYNTAX      OCTET STRING
    MAX-ACCESS  read-only
    STATUS      current
    DESCRIPTION "Host ID of WAN Memory peer"
    ::= { wmPeerEntryNew 2 }

wmPeerIp OBJECT-TYPE
    SYNTAX      IpAddress
    MAX-ACCESS  read-only
    STATUS      current
    DESCRIPTION "IP address of WAN Memory peer"
    ::= { wmPeerEntryNew 3 }

wmPeerStatus OBJECT-TYPE
    SYNTAX      OCTET STRING
    MAX-ACCESS  read-only
    STATUS      current
    DESCRIPTION "Status of WAN Memory peer"
    ::= { wmPeerEntryNew 4 }

wmPeerDiskStatus OBJECT-TYPE
    SYNTAX      OCTET STRING
    MAX-ACCESS  read-only
    STATUS      current
    DESCRIPTION "Disk status of WAN Memory peer"
    ::= { wmPeerEntryNew 5 }

wmPeerConnections OBJECT-TYPE
    SYNTAX      Unsigned32
    MAX-ACCESS  read-only
    STATUS      current
    DESCRIPTION "Number of connections through WAN Memory peer"
    ::= { wmPeerEntryNew 6 }

wmPeerSendReductionPercent OBJECT-TYPE
    SYNTAX      OCTET STRING
    MAX-ACCESS  read-only
    STATUS      current
    DESCRIPTION "TX reduction percentage for WAN Memory peer"
    ::= { wmPeerEntryNew 7 }

wmPeerReceiveReductionPercent OBJECT-TYPE
    SYNTAX      OCTET STRING
    MAX-ACCESS  read-only
    STATUS      current
    DESCRIPTION "RX reduction percentage for WAN Memory peer"
    ::= { wmPeerEntryNew 8 }


---
--- SMB Acceleration objects
---

smbV1Acceleration OBJECT IDENTIFIER
    ::= { acceleration 6 }

smbV1Enabled OBJECT-TYPE
    SYNTAX      TruthValue
    MAX-ACCESS  read-only
    STATUS      current
    DESCRIPTION "SMB v1 acceleration enabled"
    ::= { smbV1Acceleration 1 }

smbV1ReadAHead OBJECT-TYPE
    SYNTAX      TruthValue
    MAX-ACCESS  read-only
    STATUS      current
    DESCRIPTION "SMB v1 Read AHead"
    ::= { smbV1Acceleration 2 }

smbV1WriteBehind OBJECT-TYPE
    SYNTAX      TruthValue
    MAX-ACCESS  read-only
    STATUS      current
    DESCRIPTION "SMB v1 Write Behind"
    ::= { smbV1Acceleration 3 }

smbV1MetaCache OBJECT-TYPE
    SYNTAX      TruthValue
    MAX-ACCESS  read-only
    STATUS      current
    DESCRIPTION "SMB v1 Meta Cache"
    ::= { smbV1Acceleration 4 }

smbV1PrefetchBytes OBJECT-TYPE
    SYNTAX      Unsigned32
    MAX-ACCESS  read-only
    STATUS      current
    DESCRIPTION "SMB v1 Prefetch number of bytes"
    ::= { smbV1Acceleration 5 }


--
-- NOTIFICATIONS
--

notifications OBJECT IDENTIFIER
   ::= { exinda 5 }

notificationPrefix OBJECT IDENTIFIER
    ::= { notifications 0 }

cpuUtilHigh NOTIFICATION-TYPE
    STATUS  current
    DESCRIPTION
            "CPU utilization has risen too high"
    ::= { notificationPrefix 1 }

diskUsage NOTIFICATION-TYPE
    STATUS  current
    DESCRIPTION
            "Disk space on the system is low"
    ::= { notificationPrefix 2 }

memoryPaging NOTIFICATION-TYPE
    STATUS  current
    DESCRIPTION
            "The system has been paging excessively (thrashing)"
    ::= { notificationPrefix 3 }

nicCollisions NOTIFICATION-TYPE
    STATUS  current
    DESCRIPTION
            "High NIC collision rate"
    ::= { notificationPrefix 4 }

nicNegotiation NOTIFICATION-TYPE
    STATUS  current
    DESCRIPTION
            "Auto negotiation has failed"
    ::= { notificationPrefix 5 }

nicDroppedPackets NOTIFICATION-TYPE
    STATUS  current
    DESCRIPTION
            "NIC dropped packets - RX"
    ::= { notificationPrefix 6 }

nicProblemsRx NOTIFICATION-TYPE
    STATUS  current
    DESCRIPTION
            "NIC errors - RX"
    ::= { notificationPrefix 7 }

nicProblemsTx NOTIFICATION-TYPE
    STATUS  current
    DESCRIPTION
            "NIC errors - TX"
    ::= { notificationPrefix 8 }

bridgeLink NOTIFICATION-TYPE
    STATUS  current
    DESCRIPTION
            "Bridge link has failed"
    ::= { notificationPrefix 9 }

systemStartup NOTIFICATION-TYPE
    STATUS  current
    DESCRIPTION
            "System startup"
    ::= { notificationPrefix 10 }

cifsSignedConn NOTIFICATION-TYPE
    STATUS  current
    DESCRIPTION
            "CIFS Signed Connections"
    ::= { notificationPrefix 11 }

acceleratedConnLimit NOTIFICATION-TYPE
    STATUS  current
    DESCRIPTION
            "Accelerated connection limit reached"
    ::= { notificationPrefix 12 }

slaLatencyAlert NOTIFICATION-TYPE
    STATUS  current
    DESCRIPTION
            "SLA Latency threshold exceeded"
    ::= { notificationPrefix 13 }

slaLossAlert NOTIFICATION-TYPE
    STATUS  current
    DESCRIPTION
            "SLA Packet loss threshold exceeded"
    ::= { notificationPrefix 14 }

-- armNetDelayAlert NOTIFICATION-TYPE
--     STATUS  current
--     DESCRIPTION
--             "ARM Network Delay threshold exceeded"
--     ::= { notificationPrefix 15 }

-- armServerDelayAlert NOTIFICATION-TYPE
--     STATUS  current
--     DESCRIPTION
--             "ARM Server Delay threshold exceeded"
--     ::= { notificationPrefix 16 }

systemPowerLostRedundancy NOTIFICATION-TYPE
    STATUS  current
    DESCRIPTION
            "Power supply redundancy lost"
    ::= { notificationPrefix 17 }

systemStorageLostRedundancy NOTIFICATION-TYPE
    STATUS  current
    DESCRIPTION
            "Storage redundancy lost"
    ::= { notificationPrefix 18 }

systemBridgeDirection NOTIFICATION-TYPE
	STATUS current
    DESCRIPTION
            "Bridge may be connected incorrectly. Check direction."
    ::= { notificationPrefix 19 }

apsAlert NOTIFICATION-TYPE
    STATUS  current
    DESCRIPTION
            "APS threshold exceeded"
    ::= { notificationPrefix 20 }

apmAlert NOTIFICATION-TYPE
    STATUS  current
    DESCRIPTION
            "APM threshold exceeded"
    ::= { notificationPrefix 21 }

licenseExpired NOTIFICATION-TYPE
    STATUS  current
    DESCRIPTION
            "Appliance license expired"
    ::= { notificationPrefix 22 }

invalidAppliance NOTIFICATION-TYPE
    STATUS  current
    DESCRIPTION
            "Invalid Appliance"
    ::= { notificationPrefix 23 }

retryFailure NOTIFICATION-TYPE
    STATUS  current
    DESCRIPTION
            "Failed to connect Exinda license server"
    ::= { notificationPrefix 24 }

asymmetryDetection NOTIFICATION-TYPE
    STATUS  current
    DESCRIPTION
            "Asymmetric route detected on appliance"
    ::= { notificationPrefix 25 }

END
