PDU-MIB DEFINITIONS ::= BEGIN

IMPORTS
    MODULE-IDENTITY, OBJECT-TYPE, NOTIFICATION-TYPE     FROM SNMPv2-SMI
    enterprises, Integer32, Unsigned32, IpAddress   FROM SNMPv2-SMI
    MODULE-COMPLIANCE, OBJECT-GROUP, NOTIFICATION-GROUP FROM SNMPv2-CONF
    InetAddress,InetAddressType FROM INET-ADDRESS-MIB
    TEXTUAL-CONVENTION, DisplayString, MacAddress, DateAndTime, TruthValue  FROM SNMPv2-TC;

raritan MODULE-IDENTITY
    LAST-UPDATED "201602220000Z"      -- February 22,2016
    ORGANIZATION "Raritan"
    CONTACT-INFO "
                  Author:       Raritan Americas, Inc.
                  postal:       Raritan Americas, Inc.
                                400 Cottontail Lane
                                Somerset, NJ 08873
                  email:        tech@raritan.com
                  phone:        +1 732 764 8886
                 "
    DESCRIPTION  "This mib describes the SNMP functions of the Dominion PX
                  Power Distribution Unit by Raritan Computer."


    REVISION     "201602220000Z"      -- February 22,2016
    DESCRIPTION  "1) Added inletCurrentUnbalanceHysteresis to inletTable.

                  "


    REVISION     "201602030000Z"      -- February 3,2016
    DESCRIPTION  "1) Added varbind sensorDescr to the following traps
                      managingenvironmentalSensor,
                      unmanagingenvironmentalSensor.

                  "


    REVISION     "201511020000Z"      -- November 2,2015
    DESCRIPTION  "1) Added ipmiOverLAN to the info table.

                  "


    REVISION     "201510260000Z"      -- October 26,2015
    DESCRIPTION  "1) Added Comment above primaryNTPServerAddressType

                  "


    REVISION     "201510160000Z"      -- October 16,2015
    DESCRIPTION  "1) Modified DESCRIPTION clauses of the following traps.
                      ipmiOverLANEnabled,
                      ipmiOverLANDisabled

                  2)  Added the following traps to the NOTIFICATION-GROUP trapsGroup
                      ipmiOverLANEnabled,
                      ipmiOverLANDisabled

                  "

    REVISION     "201510020000Z"      -- October 2,2015
    DESCRIPTION  "1) Modified DESCRIPTION clause of thresholdAlarm trap


                  "



    REVISION     "201506190000Z"      -- June 19,2015
    DESCRIPTION  "1) Modified DESCRIPTION clauses of
                      dataLogAvgExternalSensorValue,
                      dataLogMaxExternalSensorValue,
                      dataLogAvgExternalSensorValue

                  2) Modified DESCRIPTION CLAUSE of reorderexternalSensorTableEntries

                  "


    REVISION     "201503110000Z"      -- March 11,2015
    DESCRIPTION  "1) Added the following under info.
                     thresholdValue,
                     sensorValue

                   2) Added thresholdValue and sensorValue to the following traps
                        thresholdAlarm

                  "


    REVISION     "201404030000Z"      -- April 3,2014
    DESCRIPTION  "1) Modified the DESCRIPTION of the following.
                     inletActiveEnergy
                     inletPoleMaxCurrent
                     inletPoleActivePower
                     inletPoleApparentPower
                     inletPolePowerFactor
                     inletPoleActiveEnergy
                     neutralCurrentUpperWarning
                     neutralCurrentUppeCritical
                     dataLogAvgInletPoleActivePower
                     dataLogMaxInletPoleActivePower
                     dataLogMinInletPoleActivePower
                     dataLogAvgInletPoleApparentPower
                     dataLogMaxInletPoleApparentPower
                     dataLogMinInletPoleApparentPower
                     dataLogAvgInletPoleActiveEnergy
                     dataLogMaxInletPoleActiveEnergy
                     dataLogMinInletPoleActiveEnergy
                     currentUnbalance
                   2) Added the following traps
                        managingenvironmentalSensor,
                        unmanagingenvironmentalSensor
                  "


    REVISION     "201203220000Z"      -- March 22,2012
    DESCRIPTION  "1) Added dataLogExternalSensorChanged to  dataLogExternalSensorTable.

                  "

    REVISION     "201203150000Z"      -- March 15,2012
    DESCRIPTION  "1) Added support for NTP servers.
                     Added the following objects under info
                       synchronizeWithNTPServer, useDHCPProvidedNTPServer,
                       primaryNTPServerAddressType, primaryNTPServerAddress,
                       secondaryNTPServerAddressType, secondaryNTPServerAddress,
                       daylightSavingsTime
                  "


    REVISION     "201203140000Z"      -- March 14,2012
    DESCRIPTION  "1) Added support for external sensors in the data log
                      Added dataLogExternalSensorTable
                  "

    REVISION     "201111300000Z"      -- Novemebr 30, 2011
    DESCRIPTION  "1) Modified DESCRIPTION of configureAlerts to note that Policy Name is case-sensitive
                  "


    REVISION     "201111070000Z"      -- November 7, 2011
    DESCRIPTION  "1) Added configureAlerts under info
                     Added SensorClassEnumeration, EventTypeEnumeration, EventDirectionEnumeration
                 "

    REVISION     "201110060000Z"      -- October 6, 2011
    DESCRIPTION  "1) Added fipsMode under info
                  2) Added EnabledDisabledEnumeration
                  3) Added fipsModeEnabled and fipsModeDisabled traps
                 "

    REVISION     "201105170000Z"      -- May 17, 2011
    DESCRIPTION  "1) Added altitude under info
                 "

    REVISION     "201105110000Z"      -- May 11, 2011
    DESCRIPTION  "1) Modified the DESCRIPTION clause of dataLoggingInterval and measurementsPerLogEntry
                  2) Added reorderExternaSensorTableEntries to specify the order of the entries in externalSensorTable
                  3) Added voltageMeasurementFailure trap
                 "

    REVISION     "201104180000Z"      -- April 18, 2011
    DESCRIPTION  "1) Added  dataLogAvgActivePower,dataLogMaxActivePower,dataLogMinActivePower,
                            dataLogAvgApparentPower,dataLogMaxApparentPower, dataLogMinApparentPower
                        to DataLogEntryStruct

                  2) Added  dataLogAvgOutletCurrent,dataLogMaxOutletCurrent,dataLogMinOutletCurrent,
                            dataLogAvgOutletVoltage,dataLogMaxOutletVoltage,dataLogMinOutletVoltage,
                            dataLogAvgOutletPowerFactor,dataLogMaxOutletPowerFactor,dataLogMinOutletPowerFactor,
                            dataLogAvgOutletWattHours,dataLogMaxOutletWattHours,dataLogMinOutletWattHours
                         to DataLogOutletEntryStruct

                 3) Added  dataLogAvgCircuitBreakerCurrent,dataLogMaxCircuitBreakerCurrent,dataLogMinCircuitBreakerCurrent
                         to DataLogCircuitBreakerEntryStruct

                 4) Added  dataLogAvgInletCurrentUnbalance,dataLogMaxInletCurrentUnbalance,dataLogMinInletCurrentUnbalance,
                           dataLogAvgInletActivePower,dataLogMaxInletActivePower,dataLogMinInletActivePower,
                           dataLogAvgInletApparentPower,dataLogMaxInletApparentPower,dataLogMinInletApparentPower,
                           dataLogAvgInletActiveEnergy,dataLogMaxInletActiveEnergy,dataLogMinInletActiveEnergy,
                         to DataLogInletEntryStruct

                 5) Added  dataLogAvgInletPoleCurrent,dataLogMaxInletPoleCurrent,dataLogMinInletPoleCurrent,
                           dataLogAvgInletPoleVoltage,dataLogMaxInletPoleVoltage,dataLogMinInletPoleVoltage,
                           dataLogAvgInletPoleActivePower,dataLogMaxInletPoleActivePower,dataLogMinInletPoleActivePower,
                           dataLogAvgInletPoleApparentPower,dataLogMaxInletPoleApparentPower,dataLogMinInletPoleApparentPower,
                           dataLogAvgInletPoleActiveEnergy,dataLogMaxInletPoleActiveEnergy,dataLogMinInletPoleActiveEnergy
                         to DataLogInletPoleEntryStruct

                 6) Added measurementsPerLogEntry under info.

                 7) Deprecated dataLogActivePower,dataLogApparentPower,dataLogOutletCurrent,
                               dataLogOutletVoltage,dataLogOutletPowerFactor, dataLogOutletOnTime,
                               dataLogCircuitBreakerCurrent,dataLogOutletWattHours,dataLogInletPoleCurrent,
                               dataLogInletPoleVoltage,dataLogInletCurrentUnbalance,dataLogInletActivePower,
                               dataLogInletApparentPower,dataLogInletActiveEnergy

                 8) Deprecated  dataLoggingInterval

                 "

    REVISION     "201102140000Z"      -- February 14, 2011
    DESCRIPTION  "1) Added  PowerCIMStatusEnumeration and powerCIMStatus
                  "

    REVISION     "201101240000Z"      -- January 24, 2011
    DESCRIPTION  "1) Added  lastUpgradeStatus,lastUpgradeTimestamp, lastUpgradeErrorDescription
                  "

    REVISION     "201011300000Z"      -- November 30, 2010
    DESCRIPTION  "1) Added  externalSensorNumber,externalSensorType, externalSensorName, externalSensorChannelNumber, externalBinarySensorSubtype,
                         externalSensorSerialNumber to environmentalSensorsConnectivityRestored trap
                  2) Added  externalSensorNumber,externalSensorType, externalSensorName, externalSensorChannelNumber, externalBinarySensorSubtype,
                         externalSensorSerialNumber to environmentalSensorsConnectivityLost trap
                  3) Added externalSensorSerialNumber to externalOnOffSensorStateChange
                  4) Added sensorIdentificationString to thresholdAlarm  trap
                  5) Added none to TypeOfSensorEnumeration
                  "


    REVISION     "201011040000Z"      -- November 4, 2010
    DESCRIPTION  "1) Added  environmentalSensorsConnectivityRestored trap
                  2) Changed MAX-ACCESS of inlineMeter to read-only
                  "

    REVISION     "201007210000Z"      -- July 21, 2010
    DESCRIPTION  "1) Renamed externalBinarySensorStateChange  trap to externalOnOffSensorStateChange
                  "

    REVISION     "201007190000Z"      -- July 19, 2010
    DESCRIPTION  "1) Added externalBinarySensorStateChange  trap
                  2) Added contact to TypeOfSensorEnumeration"

    REVISION     "201007150000Z"      -- July 15, 2010
    DESCRIPTION  "1) Added binary to TypeOfSensorEnumeration
                  2) Added externalBinarySensorSubtype to ExternalSensorEntryStruct"

    REVISION     "201007130000Z"      -- July 13, 2010
    DESCRIPTION  "Added outletCurrentHysteresis
                        circuitBreakerCurrentHysteresis
                        unitOrLineVoltageHysteresis,
                        unitOrLineCurrentHysteresis,
                        unitTempHysteresis,
                        currentUnbalanceHysteresis
                        inletCurrentHysteresis,
                        inletVoltageHysteresis,
                        externalSensorHysteresis"

    REVISION     "201006290000Z"      -- June 29, 2010
    DESCRIPTION  "Added externalSensorChannelNumber to externalSensorTable"

    REVISION     "201006070000Z"      -- June 7, 2010
    DESCRIPTION  "Added Alarmed to StateOfSensorEnumeration"

    REVISION     "201005270000Z"      -- May 27, 2010
    DESCRIPTION  "Moved the  externalSensorTable from under board to under pdu"

    REVISION     "201005200000Z"      -- May 20, 2010
    DESCRIPTION  "In the externalSensorTable, changed SYNTAX of externalSensorLowerCriticalThreshold,                                           externalSensorLowerWarningThreshold,externalSensorUpperCriticalThreshold,
                  externalSensorUpperWarningThreshold to Integer32"

    REVISION     "201005170000Z"      -- May 17, 2010
    DESCRIPTION  "Added externalSensorTable  for representing all types of external sensors
                  Deprecated tempSensorTable and humiditySensorTable"

    REVISION     "200906090000Z"      -- June 9, 2009
    DESCRIPTION  "Added support for multiple inlets/inline meters"


    REVISION     "200904200000Z"      -- April 20, 2009
    DESCRIPTION  "For PX 1.3.5;Deprecated SensorStateEnumeration & SensorTypeEnumeration"

    REVISION     "200902130000Z"      -- February 13, 2009
    DESCRIPTION  "For PX 1.3.5;Added support for environmental sensor coordinates:
                  added tempXCoordinate,tempYCoordinate,tempZCoordinate to tempSensorTable
                  added humidityXCoordinate,humidityYCoordinate,humidityZCoordinate to humiditySensorTable
                  added externalSensorsZCoordinateUnits under info "

    REVISION     "200902120000Z"      -- February 12, 2009
    DESCRIPTION  "For PX 1.3.5;Added support for current unbalance: enabling/disabling, unbalance value and thresholds
                  currentUnbalanceSupport,currentUnbalance,currentUnbalanceUpperWarning,currentUnbalanceUpper"


    REVISION     "200812010000Z"      -- December 1, 2008
    DESCRIPTION  "For PX 1.3;Added outletEnergySupport to indicate whether outlet energy is supported"

    REVISION     "200810240000Z"      -- October 24, 2008
    DESCRIPTION  "For PX 1.3;Added Watt-Hours for outlets, lower current warning & lower critical thresholds for outlets"


    REVISION     "200809250000Z"      -- September 25, 2008
    DESCRIPTION  "Added trap for environmental sensors disconnected"

    REVISION     "200809050000Z"      -- September 5, 2008
    DESCRIPTION  "Add support for data Log ( line, circuit breaker,outlet ) Retrieval"



    REVISION     "200806050000Z"      -- June 5, 2008
    DESCRIPTION  "PX 1.2 MIB supports 3-phase PDUs."


    REVISION     "200711280000Z"      -- November 28, 2007
    DESCRIPTION  "Modfied MIB in effort to better support HP OpenView
                  and other SNMP managers."

    REVISION     "200706200000Z"      -- June 20, 2007
    DESCRIPTION  "Updated version for remote access to pdu."
		::= { enterprises 13742 }

pdu		OBJECT IDENTIFIER ::= { raritan 4 }

traps           OBJECT IDENTIFIER ::= { pdu 0 }
board           OBJECT IDENTIFIER ::= { pdu 1 }
environmental   OBJECT IDENTIFIER ::= { pdu 2 }
externalSensors OBJECT IDENTIFIER ::= { pdu 3 }
conformance     OBJECT IDENTIFIER ::= { pdu 9 }

info            OBJECT IDENTIFIER ::= { board 1 }
outlets         OBJECT IDENTIFIER ::= { board 2 }
unit            OBJECT IDENTIFIER ::= { board 3 }
lineCurrents    OBJECT IDENTIFIER ::= { board 4 }
circuitBreaker  OBJECT IDENTIFIER ::= { board 5 }
lineVoltages    OBJECT IDENTIFIER ::= { board 6 }
dataLog         OBJECT IDENTIFIER ::= { board 7 }
inlets         OBJECT IDENTIFIER ::= { board 20 }
inletPole       OBJECT IDENTIFIER ::= { board 21 }
dataLogOutlet     OBJECT IDENTIFIER ::= { board 10 }
dataLogCircuitBreaker  OBJECT IDENTIFIER ::= { board 15 }
dataLogInputLine    OBJECT IDENTIFIER ::= { board 14 }
dataLogInlet     OBJECT IDENTIFIER ::= { board 12 }
dataLogInletPole  OBJECT IDENTIFIER ::= { board 13 }
dataLogExternalSensor  OBJECT IDENTIFIER ::= { board 16 }


unitReadings    OBJECT IDENTIFIER ::= { unit 1 }

compliances     OBJECT IDENTIFIER ::= { conformance 1 }
groups          OBJECT IDENTIFIER ::= { conformance 2 }

-- Conformance Information
-- compliance statements

compliance      MODULE-COMPLIANCE
                STATUS deprecated
                DESCRIPTION
                    "The requirements for conformance to the PDU-MIB. This is deprecated and the new compliance
                     ComplianceRev1 has been added"
                MODULE -- this module

                GROUP infoGroup
                DESCRIPTION
                    "The info group."

                GROUP outletsGroup
                DESCRIPTION
                    "The outlets group."

                GROUP unitSensorsGroup
                DESCRIPTION
                    "The unit sensor readings association group."

                GROUP externalTemperatureGroup
                DESCRIPTION
                    "The external temperature sensor association group."

                GROUP externalHumidityGroup
                DESCRIPTION
                    "The external humidity sensor association group."

                GROUP trapsGroup
                DESCRIPTION
                    "The traps group."
                ::= { compliances 1 }

complianceRev1      MODULE-COMPLIANCE
                STATUS deprecated
                DESCRIPTION
                    "The requirements for conformance to the PDU-MIB. This is deprecated and the new compliance
                     ComplianceRev2 has been added"
                MODULE -- this module

                GROUP infoGroup
                DESCRIPTION
                    "The info group."

                GROUP outletsGroup
                DESCRIPTION
                    "The outlets group."

                GROUP unitSensorsGroupRev
                DESCRIPTION
                    "The unit sensor readings association group."

                GROUP externalTemperatureGroup
                DESCRIPTION
                    "The external temperature sensor association group."

                GROUP externalHumidityGroup
                DESCRIPTION
                    "The external humidity sensor association group."

                GROUP trapsGroup
                DESCRIPTION
                    "The traps group."

                GROUP lineCurrentGroup
                DESCRIPTION
                    "The line current group."

		GROUP circuitBreakerGroup
                DESCRIPTION
                    "The Circuit Breaker group."

		GROUP lineVoltageGroup
                DESCRIPTION
                    "The line Voltage group."

                GROUP dataLogGroup
                DESCRIPTION
                    "The pdu Data group."
                ::= { compliances 2 }

complianceRev2      MODULE-COMPLIANCE
                STATUS deprecated
                DESCRIPTION
                    "The requirements for conformance to the PDU-MIB. This is deprecated and the new compliance
                     ComplianceRev3 has been added"
                MODULE -- this module

                GROUP infoGroup
                DESCRIPTION
                    "The info group."


                GROUP outletsGroup
                DESCRIPTION
                    "The outlets group."

                GROUP unitSensorsGroupRev
                DESCRIPTION
                    "The unit sensor readings association group."

                GROUP externalTemperatureGroup
                DESCRIPTION
                    "The external temperature sensor association group."

                GROUP externalHumidityGroup
                DESCRIPTION
                    "The external humidity sensor association group."

                GROUP trapsGroup
                DESCRIPTION
                    "The traps group."

		GROUP circuitBreakerGroup
                DESCRIPTION
                    "The Circuit Breaker group."

                GROUP dataLogGroup
                DESCRIPTION
                    "The pdu Data group."
                ::= { compliances 3 }


complianceRev3      MODULE-COMPLIANCE
                STATUS deprecated
                DESCRIPTION
                    "The requirements for conformance to the PDU-MIB.This is deprecated and the new compliance
                     ComplianceRev4 has been added"
                MODULE -- this module

                GROUP infoGroup
                DESCRIPTION
                    "The info group."

                GROUP inletsGroup
                DESCRIPTION
                    "The inlets group."

                GROUP outletsGroup
                DESCRIPTION
                    "The outlets group."

                GROUP unitSensorsGroupRev2
                DESCRIPTION
                    "The unit sensor readings association group."

                GROUP externalTemperatureGroup
                DESCRIPTION
                    "The external temperature sensor association group."

                GROUP externalHumidityGroup
                DESCRIPTION
                    "The external humidity sensor association group."

                GROUP trapsGroup
                DESCRIPTION
                    "The traps group."

                GROUP inletPoleGroup
                DESCRIPTION
                    "The line current group."

		GROUP circuitBreakerGroup
                DESCRIPTION
                    "The Circuit Breaker group."

                GROUP dataLogGroupRev
                DESCRIPTION
                    "The pdu Data group."
                ::= { compliances 4 }

complianceRev4      MODULE-COMPLIANCE
                STATUS deprecated
                DESCRIPTION
                    "The requirements for conformance to the PDU-MIB. This is deprecated and the new compliance
                     ComplianceRev5 has been added"
                MODULE -- this module

                GROUP infoGroup
                DESCRIPTION
                    "The info group."

                GROUP inletsGroup
                DESCRIPTION
                    "The inlets group."

                GROUP outletsGroup
                DESCRIPTION
                    "The outlets group."

                GROUP unitSensorsGroupRev2
                DESCRIPTION
                    "The unit sensor readings association group."

                GROUP externalSensorsGroup
                DESCRIPTION
                    "The external sesnors sensor association group."

                GROUP trapsGroup
                DESCRIPTION
                    "The traps group."

                GROUP inletPoleGroup
                DESCRIPTION
                    "The line current group."

		GROUP circuitBreakerGroup
                DESCRIPTION
                    "The Circuit Breaker group."

                GROUP dataLogGroupRev
                DESCRIPTION
                    "The pdu Data group."
                ::= { compliances 5 }


complianceRev5      MODULE-COMPLIANCE
                STATUS current
                DESCRIPTION
                    "The requirements for conformance to the PDU-MIB."
                MODULE -- this module

                GROUP infoGroupRev2
                DESCRIPTION
                    "The info group."

                GROUP inletsGroup
                DESCRIPTION
                    "The inlets group."

                GROUP outletsGroup
                DESCRIPTION
                    "The outlets group."

                GROUP unitSensorsGroupRev2
                DESCRIPTION
                    "The unit sensor readings association group."

                GROUP externalSensorsGroup
                DESCRIPTION
                    "The external sesnors sensor association group."

                GROUP trapsGroup
                DESCRIPTION
                    "The traps group."

                GROUP inletPoleGroup
                DESCRIPTION
                    "The line current group."

		GROUP circuitBreakerGroup
                DESCRIPTION
                    "The Circuit Breaker group."

                GROUP dataLogGroupRev2
                DESCRIPTION
                    "The pdu Data group."
                ::= { compliances 6 }

-- units of conformance

infoGroup       OBJECT-GROUP
                OBJECTS {
                          dataLoggingInterval
                         }
                STATUS  deprecated
                DESCRIPTION
                    "A collection of objects providing basic information
                     about the pdu."
                ::= { groups 1 }

infoGroupRev2       OBJECT-GROUP
                OBJECTS { firmwareVersion,
                          serialNumber,
                          ipAddress,
                          netmask,
                          gateway,
                          mac,
                          hardwareRev,
                          userName,
                          objectName,
                          objectInstance,
                          targetUser,
                          groupName,
                          imageVersion,
                          sensorDescr,
                          thresholdDescr,
                          thresholdSeverity,
                          thresholdEventType,
                          status,
                          slaveIpAddress,
                          inputCurrentRating,
                          ratedVoltage,
                          ratedPower,
                          outletSwitching,
                          dataLogging,
                          dataCollectionInterval,
                          outletEnergySupport,
                          currentUnbalanceSupport,
                          externalSensorsZCoordinateUnits,
                          inlineMeter,
                          oldSensorState,
                          externalSensorNumber,
                          sensorIdentificationString,
                          lastUpgradeStatus,
                          lastUpgradeTimestamp,
                          lastUpgradeErrorDescription,
                          powerCIMStatus,
                          measurementsPerLogEntry,
                          psocNumber,
                          altitude,
                          configureAlerts,
                          fipsMode,
                          synchronizeWithNTPServer,
                          useDHCPProvidedNTPServer,
                          primaryNTPServerAddressType,
                          primaryNTPServerAddress,
                          secondaryNTPServerAddressType,
                          secondaryNTPServerAddress,
                          daylightSavingsTime,
                          thresholdValue,
                          sensorValue,
                          ipmiOverLAN
                         }
                STATUS  current
                DESCRIPTION
                    "A collection of objects providing basic information
                     about the pdu."
                ::= { groups 22 }


outletsGroup    OBJECT-GROUP
                OBJECTS { outletCount,
                          outletLabel,
                          outletCurrentRating,
                          outletOperationalState,
                          outletCurrent,
                          outletMaxCurrent,
                          outletVoltage,
                          outletActivePower,
                          outletApparentPower,
                          outletPowerFactor,
                          outletCurrentUpperWarning,
                          outletCurrentUpperCritical,
                          outletCurrentLowerWarning,
                          outletCurrentLowerCritical,
                          outletCurrentHysteresis,
                          outletWattHours
                          }
                STATUS  current
                DESCRIPTION
                    "A collection of objects providing basic information
                     about the outlets, including sensor readings."
                ::= { groups 2 }

unitSensorsGroup          OBJECT-GROUP
                          OBJECTS {
                                    unitCurrent,
                                    unitVoltage,
                                    unitActivePower,
                                    unitApparentPower,
                                    unitCpuTemp,
                                    unitVoltageLowerWarning,
                                    unitVoltageUpperWarning,
                                    unitVoltageLowerCritical,
                                    unitVoltageUpperCritical,
                                    unitCurrentUpperWarning,
                                    unitCurrentUpperCritical,
                                    unitTempLowerWarning,
                                    unitTempUpperWarning,
                                    unitTempLowerCritical,
                                    unitTempUpperCritical }
                          STATUS  deprecated
                          DESCRIPTION
                              "A collection of objects providing unit level sensor readings.This group is deprecated in favor
                               of unitSensorsGroupRev"
                          ::= { groups 4 }



externalTemperatureGroup   OBJECT-GROUP
                           OBJECTS { tempSensorCount,
                                     tempSensorLabel,
                                     temperature,
                                     tempLowerWarning,
                                     tempUpperWarning,
                                     tempLowerCritical,
                                     tempUpperCritical,
                                     tempXCoordinate,
                                     tempYCoordinate,
                                     tempZCoordinate
                                     }
                           STATUS  deprecated
                           DESCRIPTION
                               "A collection of objects providing external temperature sensor readings and
                                  threshold settings. This group is deprecated in favor of the externalSensorsGroup"
                           ::= { groups 6 }

externalHumidityGroup   OBJECT-GROUP
                        OBJECTS { humiditySensorCount,
                                  humiditySensorLabel,
                                  humidity,
                                  humidityLowerWarning,
                                  humidityUpperWarning,
                                  humidityLowerCritical,
                                  humidityUpperCritical,
                                  humidityXCoordinate,
                                  humidityYCoordinate,
                                  humidityZCoordinate }
                        STATUS  deprecated
                        DESCRIPTION
                            "A collection of objects providing external humidity sensor readings and threshold settings.
                             This group is deprecated in favor of the externalSensorsGroup"
                        ::= { groups 7 }

trapsGroup      NOTIFICATION-GROUP
                NOTIFICATIONS { rebootStarted,
                                rebootCompleted,
                                userLogin,
                                userLogout,
                                userAuthenticationFailure,
                                userSessionTimeout,
                                userAdded,
                                userModified,
                                userDeleted,
                                groupAdded,
                                groupModified,
                                groupDeleted,
                                deviceUpdateStarted,
                                userBlocked,
                                powerControl,
                                userPasswordChanged,
                                passwordSettingsChanged,
                                firmwareFileDiscarded,
                                firmwareValidationFailed,
                                securityViolation,
                                logFileCleared,
                                thresholdAlarm,
                                outletGroupingConnectivityLost,
                                circuitBreakerTripped,
                                circuitBreakerRecovered,
                                bulkConfigurationSaved,
                                bulkConfigurationCopied,
                                environmentalSensorsConnectivityLost,
                                externalOnOffSensorStateChange,
                                environmentalSensorsConnectivityRestored,
                                voltageMeasurementError,
                                fipsModeEnabled,
                                fipsModeDisabled,
                                managingenvironmentalSensor,
                                unmanagingenvironmentalSensor,
                                ipmiOverLANEnabled,
                                ipmiOverLANDisabled
                                     }
                STATUS  current
                DESCRIPTION
                    "A collection of traps."
                ::= { groups 9 }

lineCurrentGroup   OBJECT-GROUP
                           OBJECTS { lineCurrentCount,
                                     lineCurrentLabel,
                                     lineCurrent}
                           STATUS  deprecated
                           DESCRIPTION
                               "A collection of objects describing the line inputs.
                                This group is deprecated in favor of inletPoleGroup"
                           ::= { groups 10 }


circuitBreakerGroup   OBJECT-GROUP
                           OBJECTS { circuitBreakerCount,
                                     circuitBreakerLabel,
                                     circuitBreakerCurrentRating,
				     circuitBreakerState,
                                     circuitBreakerCurrent,
                                     circuitBreakerCurrentUpperWarning,
                                     circuitBreakerCurrentUpperCritical,
                                     circuitBreakerCurrentHysteresis }
                           STATUS  current
                           DESCRIPTION
                               "A collection of objects describing the circuit breakers."
                           ::= { groups 11 }

lineVoltageGroup   OBJECT-GROUP
                           OBJECTS { lineVoltageCount,
                                     lineVoltageLabel,
                                     lineVoltage}
                           STATUS  deprecated
                           DESCRIPTION
                               "A collection of objects describing the line voltages.
                                This group is deprecated in favor of inletPoleGroup"
                           ::= { groups 12 }

unitSensorsGroupRev          OBJECT-GROUP
                          OBJECTS {
                                    unitActivePower,
                                    unitApparentPower,
                                    unitCpuTemp,
				    unitOrLineVoltageLowerWarning,
                                    unitOrLineVoltageUpperWarning,
                                    unitOrLineVoltageLowerCritical,
                                    unitOrLineVoltageUpperCritical,
                                    unitOrLineCurrentUpperWarning,
                                    unitOrLineCurrentUpperCritical,
                                    neutralCurrentUpperWarning,
                                    neutralCurrentUpperCritical,
                                    unitTempLowerWarning,
                                    unitTempUpperWarning,
                                    unitTempLowerCritical,
                                    unitTempUpperCritical,
                                    currentUnbalance,
                                    currentUnbalanceUpperWarning,
                                    currentUnbalanceUpperCritical}
                          STATUS  deprecated
                          DESCRIPTION
                              "A collection of objects providing unit level sensor readings.This group is deprecated
                               in favor of unitSensorsGroupRev2"
                          ::= { groups 13 }

unitSensorsGroupRev2          OBJECT-GROUP
                          OBJECTS {
                                    unitCpuTemp,
				    unitOrLineVoltageLowerWarning,
                                    unitOrLineVoltageUpperWarning,
                                    unitOrLineVoltageLowerCritical,
                                    unitOrLineVoltageUpperCritical,
                                    unitOrLineCurrentUpperWarning,
                                    unitOrLineCurrentUpperCritical,
                                    neutralCurrentUpperWarning,
                                    neutralCurrentUpperCritical,
                                    unitTempLowerWarning,
                                    unitTempUpperWarning,
                                    unitTempLowerCritical,
                                    unitTempUpperCritical,
                                    currentUnbalance,
                                    currentUnbalanceUpperWarning,
                                    currentUnbalanceUpperCritical,
                                    unitOrLineVoltageHysteresis,
                                    unitOrLineCurrentHysteresis,
                                    unitTempHysteresis,
                                    currentUnbalanceHysteresis}
                          STATUS  current
                          DESCRIPTION
                              "A collection of objects providing unit level sensor readings."
                          ::= { groups 18 }

dataLogGroup   OBJECT-GROUP
                           OBJECTS { dataLogCount,
                                     dataLogLatestIndex,
                                     dataLogTimeStamp,
                                     dataLogActivePower,
                                     dataLogApparentPower,
                                     dataLogOutletCurrent,
                                     dataLogOutletVoltage,
                                     dataLogOutletPowerFactor,
                                     dataLogOutletOnTime,
                                     dataLogCircuitBreakerCurrent,
                                     dataLogInputLineCurrent,
                                     dataLogInputLineVoltage,
                                     dataLogOutletWattHours

                                     }
                           STATUS  deprecated
                           DESCRIPTION
                               "A collection of objects describing the pdu data.
                                This group is being deprecated in favor of dataLogGroupRev "
                           ::= { groups 14 }

dataLogGroupRev   OBJECT-GROUP
                           OBJECTS { dataLogCount,
                                     dataLogLatestIndex,
                                     dataLogTimeStamp,
                                     dataLogActivePower,
                                     dataLogApparentPower,
                                     dataLogOutletCurrent,
                                     dataLogOutletVoltage,
                                     dataLogOutletPowerFactor,
                                     dataLogOutletOnTime,
                                     dataLogCircuitBreakerCurrent,
                                     dataLogOutletWattHours,
                                     dataLogInletPoleCurrent,
                                     dataLogInletPoleVoltage,
                                     dataLogInletCurrentUnbalance,
                                     dataLogInletActivePower,
                                     dataLogInletApparentPower,
                                     dataLogInletActiveEnergy
                                     }
                           STATUS  deprecated
                           DESCRIPTION
                               "A collection of objects describing the pdu data.
                                This group is being deprecated in favor of dataLogGroupRev2"
                           ::= { groups 17 }

dataLogGroupRev2   OBJECT-GROUP
                           OBJECTS { dataLogCount,
                                     dataLogLatestIndex,
                                     dataLogTimeStamp,
                                     dataLogAvgActivePower,
                                     dataLogMaxActivePower,
                                     dataLogMinActivePower,
                                     dataLogAvgApparentPower,
                                     dataLogMaxApparentPower,
                                     dataLogMinApparentPower,
                                     dataLogAvgOutletCurrent,
                                     dataLogMaxOutletCurrent,
                                     dataLogMinOutletCurrent,
                                     dataLogAvgOutletVoltage,
                                     dataLogMaxOutletVoltage,
                                     dataLogMinOutletVoltage,
                                     dataLogAvgOutletPowerFactor,
                                     dataLogMaxOutletPowerFactor,
                                     dataLogMinOutletPowerFactor,
                                     dataLogAvgOutletWattHours,
                                     dataLogMaxOutletWattHours,
                                     dataLogMinOutletWattHours,
                                     dataLogAvgCircuitBreakerCurrent,
                                     dataLogMaxCircuitBreakerCurrent,
                                     dataLogMinCircuitBreakerCurrent,
                                     dataLogAvgInletCurrentUnbalance,
                                     dataLogMaxInletCurrentUnbalance,
                                     dataLogMinInletCurrentUnbalance,
                                     dataLogAvgInletActivePower,
                                     dataLogMaxInletActivePower,
                                     dataLogMinInletActivePower,
                                     dataLogAvgInletApparentPower,
                                     dataLogMaxInletApparentPower,
                                     dataLogMinInletApparentPower,
                                     dataLogAvgInletActiveEnergy,
                                     dataLogMaxInletActiveEnergy,
                                     dataLogMinInletActiveEnergy,
                                     dataLogAvgInletPoleCurrent,
                                     dataLogMaxInletPoleCurrent,
                                     dataLogMinInletPoleCurrent,
                                     dataLogAvgInletPoleVoltage,
                                     dataLogMaxInletPoleVoltage,
                                     dataLogMinInletPoleVoltage,
                                     dataLogAvgInletPoleActivePower,
                                     dataLogMaxInletPoleActivePower,
                                     dataLogMinInletPoleActivePower,
                                     dataLogAvgInletPoleApparentPower,
                                     dataLogMaxInletPoleApparentPower,
                                     dataLogMinInletPoleApparentPower,
                                     dataLogAvgInletPoleActiveEnergy,
                                     dataLogMaxInletPoleActiveEnergy,
                                     dataLogMinInletPoleActiveEnergy,
                                     dataLogExternalSensorChanged,
                                     dataLogExternalSensorState,
                                     dataLogAvgExternalSensorValue,
                                     dataLogMaxExternalSensorValue,
                                     dataLogMinExternalSensorValue
                                     }
                           STATUS  current
                           DESCRIPTION
                               "A collection of objects describing the pdu data."
                           ::= { groups 21 }


inletPoleGroup   OBJECT-GROUP
                           OBJECTS { inletPoleCount,
                                     inletPoleLabel,
                                     inletPoleCurrent,
                                     inletPoleVoltage,
                                     inletPoleMaxCurrent,
                                     inletPoleActivePower,
                                     inletPoleApparentPower,
                                     inletPolePowerFactor,
                                     inletPoleActiveEnergy
                                     }
                           STATUS  current
                           DESCRIPTION
                               "A collection of objects describing the inlet poles."
                           ::= { groups 15 }

inletsGroup    OBJECT-GROUP
                OBJECTS { inletCount,
                          inletCurrentRating,
                          inletCurrentUnbalanceUpperCritical,
                          inletCurrentUnbalanceUpperWarning,
                          inletCurrentUnbalance,
                          inletActivePower,
                          inletApparentPower,
                          inletPoleCount,
                          inletCurrent,
                          inletVoltage,
                          inletPowerFactor,
                          inletActiveEnergy,
                          inletCurrentUpperWarning,
                          inletCurrentUpperCritical,
                          inletCurrentLowerWarning,
                          inletCurrentLowerCritical,
                          inletVoltageUpperWarning,
                          inletVoltageUpperCritical,
                          inletVoltageLowerWarning,
                          inletVoltageLowerCritical,
                          inletCurrentHysteresis,
                          inletVoltageHysteresis,
                          inletCurrentUnbalanceHysteresis
                          }
                STATUS  current
                DESCRIPTION
                    "A collection of objects providing basic information
                     about the inlets, including sensor readings."
                ::= { groups 16 }

externalSensorsGroup   OBJECT-GROUP
                           OBJECTS { externalSensorCount,
                                    externalSensorType,
                                    externalSensorSerialNumber,
                                    externalSensorName,
                                    externalSensorChannelNumber,
                                    externalSensorXCoordinate,
                                    externalSensorYCoordinate,
                                    externalSensorZCoordinate,
                                    externalBinarySensorSubtype,
                                    externalSensorUnits,
                                    externalSensorDecimalDigits,
                                    externalSensorLowerCriticalThreshold,
                                    externalSensorLowerWarningThreshold,
                                    externalSensorUpperCriticalThreshold,
                                    externalSensorUpperWarningThreshold,
                                    externalSensorState,
                                    externalSensorValue,
                                    externalSensorHysteresis,
                                    reorderexternalSensorTableEntries
                                     }
                           STATUS  current
                           DESCRIPTION
                               "A collection of objects providing external  sensor readings
                                and configuration settings."
                           ::= { groups 20 }

-- Textual Conventions

MilliAmps       ::= TEXTUAL-CONVENTION
                DISPLAY-HINT "d"
                STATUS        current
                DESCRIPTION
                    "Data type for reporting sensor readings and thresholds
                    associated with current sensors. If the underlying hardware
                    sensor indicates 1 amp, then the SNMP agent will report
                    a value of 1000 milliamps.  The value is scaled in this
                    manner as a way to deal with floating point types
                    that SNMP does not currently support."
                SYNTAX Unsigned32

MilliVolts      ::= TEXTUAL-CONVENTION
                DISPLAY-HINT "d"
                STATUS      current
                DESCRIPTION
                    "Data type for reporting sensor readings and thresholds
                    associated with voltage sensors. If the underlying hardware
                    sensor indicates 1 volts, then the SNMP agent will report
                    a value of 1000 millivolts.  The value is scaled in this
                    manner as a way to deal with floating point types
                    that SNMP does not currently support."
                SYNTAX Unsigned32

Watts           ::= TEXTUAL-CONVENTION
                DISPLAY-HINT "d"
                STATUS      current
                DESCRIPTION
                    "Data type for reporting sensor readings and thresholds
                    associated with active power sensors. If the underlying hardware
                    sensor indicates 1 watt, then the SNMP agent will report
                    a value of 1 watt. No scaling is performed for this type."
                SYNTAX Unsigned32

VoltAmps        ::= TEXTUAL-CONVENTION
                DISPLAY-HINT "d"
                STATUS      current
                DESCRIPTION
                    "Data type for reporting sensor readings and thresholds
                    associated with apparent power sensors. If the underlying hardware
                    sensor indicates 1 volt-amp, then the SNMP agent will report
                    a value of 1 volt-amp. No scaling is performed for this type."
                SYNTAX Unsigned32

DegreesCelsius  ::= TEXTUAL-CONVENTION
                DISPLAY-HINT "d"
                STATUS      current
                DESCRIPTION
                    "Data type for reporting  thresholds
                    associated with temperature sensors. If the underlying hardware
                    sensor indicates 1 degree Celsius, then the SNMP agent will report
                    a value of 1 degree Celsius. No scaling is performed for this type."
                SYNTAX Unsigned32

TenthDegreesCelsius  ::= TEXTUAL-CONVENTION
                DISPLAY-HINT "d"
                STATUS      current
                DESCRIPTION
                    "Data type for reporting sensor readings
                    associated with temperature sensors. If the underlying hardware
                    sensor indicates 1 degree Celsius, then the SNMP agent will report
                    a value of 10  tenth degrees Celsius. The value is scaled in this
                    manner as a way to deal with floating point types
                    that SNMP does not currently support."
                SYNTAX Unsigned32

Hertz           ::= TEXTUAL-CONVENTION
                DISPLAY-HINT "d"
                STATUS      current
                DESCRIPTION
                    "Data type for reporting sensor readings and thresholds
                    associated with frequency sensors. If the underlying hardware
                    sensor indicates 1 Hertz, then the SNMP agent will report
                    a value of 1 Hertz. No scaling is performed for this type."
                SYNTAX Unsigned32

RelativeHumidity   ::= TEXTUAL-CONVENTION
                   DISPLAY-HINT "d"
                   STATUS      current
                   DESCRIPTION
                       "Data type for reporting sensor readings and thresholds
                       associated with humidity sensors. Relative humidity is
                       expressed as percentage and is defined as the ratio of the
                       partial pressure of water vapor in a gaseous mixture of
                       air and water vapor to the saturated vapor pressure of water
                       at a given temperature."
                   SYNTAX Unsigned32 (0..100)

PowerFactorPercentage   ::= TEXTUAL-CONVENTION
                   DISPLAY-HINT "d"
                   STATUS      current
                   DESCRIPTION
                       "Data type for reporting sensor readings and thresholds
                       associated with power factor sensors. The power factor of
                       an AC power system is defined as the ratio of the real
                       or active power to the apparent power and is a number
                       between 0 and 1.  A PowerFactorPercentage value is calculated
                       by taking this ratio and multiplying by 100.  The power factor
                       is used to indicate how efficiently a particular load is
                       utilizing energy."
                   SYNTAX Unsigned32 (0..100)

Percentage   ::= TEXTUAL-CONVENTION
                   DISPLAY-HINT "d"
                   STATUS      current
                   DESCRIPTION
                       "Data type for reporting values in percentage."
                   SYNTAX Unsigned32 (0..100)

SensorTypeEnumeration ::= TEXTUAL-CONVENTION
                          STATUS  deprecated
                          DESCRIPTION
                              "The types a sensor can be. This enumeration is deprecated starting with PX 1.3.5"
                          SYNTAX        INTEGER { outletCurrent(0),
                                                  outletMaxCurrent(1),
                                                  outletVoltage(2),
                                                  outletActivePower(3),
                                                  outletApparentPower(4),
                                                  outletMaxActivePower(5),
                                                  outletAverageActivePower(6),
                                                  outletPowerFactor(7),
                                                  powerBranchVoltage(200),
                                                  powerBranchFrequency(201),
                                                  powerBranchTemperature(202),
                                                  powerBranchCurrent(203),
                                                  environmentalTemp1(300),
                                                  environmentalTemp2(301),
                                                  environmentalTemp3(302),
                                                  environmentalTemp4(303),
                                                  environmentalTemp5(304),
                                                  environmentalTemp6(305),
                                                  environmentalTemp7(306),
                                                  environmentalTemp8(307),
                                                  environmentalHumidity1(400),
                                                  environmentalHumidity2(401),
                                                  environmentalHumidity3(402),
                                                  environmentalHumidity4(403),
                                                  environmentalHumidity5(404),
                                                  environmentalHumidity6(405),
                                                  environmentalHumidity7(406),
                                                  environmentalHumidity8(407),
                                                  unitRmsCurrent(500),
                                                  unitMaxRmsCurrent(501),
                                                  unitVoltage(502),
                                                  unitCpuTemp(503),
                                                  unitActivePower(504),
                                                  unitApparentPower(505),
                                                  unitFrequency(506),
                                                  unitCircuitBreak0State(550),
                                                  unitCircuitBreak1State(551),
                                                  unitCircuitBreak2State(552),
                                                  unitCircuitBreak0Current(600),
                                                  unitCircuitBreak1Current(601),
                                                  unitCircuitBreak2Current(602) }

SensorStateEnumeration ::= TEXTUAL-CONVENTION
                           STATUS  deprecated
                           DESCRIPTION
                               "The states a sensor can be in.This enumeration is deprecated starting with PX 1.3.5"
                           SYNTAX        INTEGER { unavailable(-1),
                                                   ok(0),
                                                   belowLowerWarning(1),
                                                   aboveUpperWarning(2),
                                                   belowLowerCritical(3),
                                                   aboveUpperCritical(4) }

StateOfSensorEnumeration ::= TEXTUAL-CONVENTION
                           STATUS  current
                           DESCRIPTION
                               "The states a sensor can be in."
                           SYNTAX        INTEGER { unavailable(-1),
                                                   open(0),
                                                   closed(1),
                                                   belowLowerCritical(2),
                                                   belowLowerWarning(3),
                                                   normal(4),
                                                   aboveUpperWarning(5),
                                                   aboveUpperCritical(6),
                                                   on(7),
                                                   off(8),
                                                   detected(9),
                                                   notDetected(10),
                                                   alarmed(11)

                                                 }

TypeOfSensorEnumeration ::= TEXTUAL-CONVENTION
                          STATUS  current
                          DESCRIPTION
                              "The types a sensor can be."
                          SYNTAX        INTEGER {
                                                  rmsCurrent(1),
                                                  peakCurrent(2),
                                                  unbalancedCurrent(3),
                                                  rmsVoltage(4),
                                                  activePower(5),
                                                  apparentPower(6),
                                                  powerFactor(7),
                                                  activeEnergy(8),
                                                  apparentEnergy(9),
                                                  temperature(10),
                                                  humidity(11),
                                                  airFlow(12),
                                                  airPressure(13),
                                                  onOff(14),
                                                  trip(15),
                                                  vibration(16),
                                                  waterDetection(17),
                                                  smokeDetection(18),
                                                  binary(19),
                                                  contact(20),
                                                  other(30),
                                                  none(31)
                                                   }

WattHours           ::= TEXTUAL-CONVENTION
                DISPLAY-HINT "d"
                STATUS      current
                DESCRIPTION
                    "Data type for reporting the active energy"
                SYNTAX Unsigned32

SensorUnitsEnumeration ::= TEXTUAL-CONVENTION
                          STATUS  current
                          DESCRIPTION
                              "The types a sensor can be."
                          SYNTAX        INTEGER { none(-1),
                                                  other(0),
                                                  volt(1),
                                                  amp(2),
                                                  watt(3),
                                                  voltamp(4),
                                                  wattHour(5),
                                                  voltampHour(6),
                                                  degreeC(7),
                                                  hertz(8),
                                                  percent(9),
                                                  meterpersec(10),
                                                  pascal(11),
                                                  psi(12),
                                                  g(13),
                                                  degreeF(14),
                                                  feet(15),
                                                  inches(16),
                                                  cm(17),
                                                  meters(18)
                                                  }


PowerCIMStatusEnumeration ::= TEXTUAL-CONVENTION
                          STATUS  current
                          DESCRIPTION
                              "The status of a PowerCIM"
                          SYNTAX        INTEGER { off(0),
                                                  on(1)
                                                  }

EnabledDisabledEnumeration ::= TEXTUAL-CONVENTION
                          STATUS  current
                          DESCRIPTION
                              "The status of a PowerCIM"
                          SYNTAX        INTEGER { disabled(0),
                                                  enabled(1)
                                                  }

SensorClassEnumeration ::= TEXTUAL-CONVENTION
                          STATUS  current
                          DESCRIPTION
                              "The class of sensor in the event"
                          SYNTAX        INTEGER { externalTemperature(0),
                                                  externalHumidity(1),
						  externalAirFlow(2),
						  externalAirPressure(3)
                                                  }

EventTypeEnumeration ::= TEXTUAL-CONVENTION
                          STATUS  current
                          DESCRIPTION
                              "The event type"
                          SYNTAX        INTEGER { aboveUpperCritical(0),
                                                  aboveUpperNonCritical(1),
                                                  belowLowerNonCritical(2),
                                                  belowLowerCritical(3)
                                                  }
EventDirectionEnumeration ::= TEXTUAL-CONVENTION
                          STATUS  current
                          DESCRIPTION
                              "The event direction"
                          SYNTAX        INTEGER { asserted(0),
                                                  deasserted(1),
                                                  both(2)
                                                  }

-- the info group

firmwareVersion OBJECT-TYPE
                SYNTAX        DisplayString
                MAX-ACCESS    read-only
                STATUS        current
                DESCRIPTION
                    "The current firmware version in the following format:
                     major.minor.dot.buildnumber.
                     Example: 1.3.5.7416"
                ::= { info 1 }

serialNumber    OBJECT-TYPE
                SYNTAX        DisplayString
                MAX-ACCESS    read-only
                STATUS        current
                DESCRIPTION
                    "The serial number."
                ::= { info 2 }

ipAddress       OBJECT-TYPE
                SYNTAX        IpAddress
                MAX-ACCESS    read-only
                STATUS        current
                DESCRIPTION
                    "The current IP address. A value of 0.0.0.0 indicates an error
                     or an unset option."
                ::= { info 3 }

netmask         OBJECT-TYPE
                SYNTAX        IpAddress
                MAX-ACCESS    read-only
                STATUS        current
                DESCRIPTION
                    "The current Netmask. A value of 0.0.0.0 indicates an error
                     or an unset option."
                ::= { info 4 }

gateway         OBJECT-TYPE
                SYNTAX        IpAddress
                MAX-ACCESS    read-only
                STATUS        current
                DESCRIPTION
                    "The current Gateway. A value of 0.0.0.0 indicates an error
                     or an unset option."
                ::= { info 5 }

mac             OBJECT-TYPE
                SYNTAX        MacAddress
                MAX-ACCESS    read-only
                STATUS        current
                DESCRIPTION
                    "The current MAC address."
                ::= { info 6 }

hardwareRev     OBJECT-TYPE
                SYNTAX        Integer32(0..255)
                MAX-ACCESS    read-only
                STATUS        current
                DESCRIPTION
                    "The hardware revision number."
                ::= { info 7 }

userName        OBJECT-TYPE
                SYNTAX        DisplayString
                MAX-ACCESS    accessible-for-notify
                STATUS        current
                DESCRIPTION
                    "The login of a user."
                ::= { info 10 }

objectName      OBJECT-TYPE
                SYNTAX        DisplayString
                MAX-ACCESS    accessible-for-notify
                STATUS        current
                DESCRIPTION
                    "The model type of the device"
                ::= { info 12 }

objectInstance  OBJECT-TYPE
                SYNTAX        DisplayString
                MAX-ACCESS    accessible-for-notify
                STATUS        current
                DESCRIPTION
                    "The device name."
                ::= { info 13}

targetUser      OBJECT-TYPE
                SYNTAX        DisplayString
                MAX-ACCESS    accessible-for-notify
                STATUS        current
                DESCRIPTION
                    "The user record being operated on"
                ::= { info 14}

groupName       OBJECT-TYPE
                SYNTAX        DisplayString
                MAX-ACCESS    accessible-for-notify
                STATUS        current
                DESCRIPTION
                    "The group record being operated on"
                ::= { info 15 }

imageVersion    OBJECT-TYPE
                SYNTAX        DisplayString
                MAX-ACCESS    accessible-for-notify
                STATUS        current
                DESCRIPTION
                    "The version of the Upgrade image"
                ::= { info 18 }

sensorDescr     OBJECT-TYPE
                SYNTAX        DisplayString
                MAX-ACCESS    accessible-for-notify
                STATUS        current
                DESCRIPTION
                    "Sensor description indicating which sensor experienced a threshold event.
                      When applicable, the description will indicate the sensor number."
                ::= { info 19 }

thresholdDescr  OBJECT-TYPE
                SYNTAX        DisplayString
                MAX-ACCESS    accessible-for-notify
                STATUS        current
                DESCRIPTION
                    "Threshold description indicating which configured threshold has been triggered (or cleared)."
                ::= { info 20 }

thresholdSeverity  OBJECT-TYPE
                SYNTAX        DisplayString
                MAX-ACCESS    accessible-for-notify
                STATUS        current
                DESCRIPTION
                    "String (Warning, Critical, etc...) indicating the severity of the threshold which has been triggered (or cleared)."
                ::= { info 21 }

thresholdEventType OBJECT-TYPE
                SYNTAX        DisplayString
                MAX-ACCESS    accessible-for-notify
                STATUS        current
                DESCRIPTION
                    "String (triggered, cleared) indicating if the threshold event indicates that a configured threshold
                     has been triggered or cleared."
                ::= { info 22 }

status          OBJECT-TYPE
                SYNTAX        DisplayString
                MAX-ACCESS    accessible-for-notify
                STATUS        current
                DESCRIPTION
                    "The success status of an operation"
                ::= { info 23 }

slaveIpAddress  OBJECT-TYPE
                SYNTAX        IpAddress
                MAX-ACCESS    read-only
                STATUS        current
                DESCRIPTION
                    "In an outlet grouping configuration, this is the IP address of slave PDU. A value of 0.0.0.0 indicates an error
                     or an unset option."
                ::= { info 24}


inputCurrentRating  OBJECT-TYPE
                SYNTAX        MilliAmps
                MAX-ACCESS    read-only
                STATUS        current
                DESCRIPTION
                    "The input current Rating"
                ::= { info 25}

ratedVoltage       OBJECT-TYPE
                SYNTAX        DisplayString
                MAX-ACCESS    read-only
                STATUS        current
                DESCRIPTION
                    "PDU Rated Voltage "
                ::= { info 26 }

ratedPower       OBJECT-TYPE
                SYNTAX        DisplayString
                MAX-ACCESS    read-only
                STATUS        current
                DESCRIPTION
                    "PDU Rated Power "
                ::= { info 27 }


outletSwitching          OBJECT-TYPE
                SYNTAX        DisplayString
                MAX-ACCESS    read-write
                STATUS        current
                DESCRIPTION
                    "Outlet switching: enabled/disabled; for non-switched PDUs, this value can be read,
                     but cannot be written "
                ::= { info 28 }

dataLogging          OBJECT-TYPE
                SYNTAX        DisplayString
                MAX-ACCESS    read-write
                STATUS        current
                DESCRIPTION
                    "Data Retrieval: enabled/disabled"
                ::= { info 29 }


dataLoggingInterval       OBJECT-TYPE
                SYNTAX        Integer32
                MAX-ACCESS    read-write
                STATUS        deprecated
                DESCRIPTION
                    "Data Logging periodicity in seconds. This is the periodicity of the data in the buffer.
                     This value must be a multiple of 3 between 3 and 600. For example, 60 is valid,
                     but 64 is not valid
                     This is being deprecated in favor of measurementsPerLogEntry.
                     The mapping is as follows.

                      dataLoggingInterval   measurementsPerLogEntry
                            3n                      n

                      Example:  dataLoggingInterval  is 60, so every 60 seconds (or 20th sample)
                                     data will be placed in the data log
                                measurementsPerLogEntry is 20, so the data log sill store the minimum, average
                                 and maximum of every 20 samples
                      "
                ::= { info 30 }

dataCollectionInterval       OBJECT-TYPE
                SYNTAX        Integer32
                MAX-ACCESS    read-only
                STATUS        current
                DESCRIPTION
                    "Data Collection periodicity. This is the periodicity of the data collected by the PX. This value
                     is fixed at 3 seconds."
                ::= { info 31 }

outletEnergySupport          OBJECT-TYPE
                SYNTAX        DisplayString
                MAX-ACCESS    read-only
                STATUS        current
                DESCRIPTION
                    "Outlet Energy Support: Yes/No
                      If the value is No, then outletWattHours and dataLogOutletWattHours will be zero "
                ::= { info 32 }

currentUnbalanceSupport          OBJECT-TYPE
                SYNTAX        DisplayString
                MAX-ACCESS    read-write
                STATUS        current
                DESCRIPTION
                    "current Unbalance calculations Supported: Yes/No
                      If the value is No, then currentUnbalance  will be zero
                      Default is No "
                ::= { info 33 }

externalSensorsZCoordinateUnits   OBJECT-TYPE
                SYNTAX        DisplayString
                MAX-ACCESS    read-write
                STATUS        current
                DESCRIPTION
                    "External Sensor Z Coordinate units: Freeform or Rack Units (U)
                     Default is U "
                ::= { info 34 }

inlineMeter          OBJECT-TYPE
                SYNTAX        DisplayString
                MAX-ACCESS    read-only
                STATUS        current
                DESCRIPTION
                    "Is this unit an inline meter? Yes/No
                     If Yes, then the folowing pairings hold:
                     Inlet 1  <-> Outlet 1
                     Inlet 2  <-> Outlet 2
                     Inlet 3  <-> Outlet 3
                     Inlet 4  <-> Outlet 4

                     Use the inletTable to obtain inlet data

                     Use the inletPoleTable to obtain the line data for an inlet.

                     "
                ::= { info 35 }


oldSensorState      OBJECT-TYPE
                    SYNTAX        StateOfSensorEnumeration
                    MAX-ACCESS    accessible-for-notify
                    STATUS        current
                    DESCRIPTION
                         "The old sensor state used in Sensor State Transition traps."
                    ::= { info 36}


externalSensorNumber    OBJECT-TYPE
                        SYNTAX        Integer32(1..256)
                        MAX-ACCESS    accessible-for-notify
                        STATUS        current
                        DESCRIPTION
                          "A unique value for each sensor. Its value
                            ranges between 1 and the value of externalSensorCount."
                        ::= { info 37  }



sensorIdentificationString   OBJECT-TYPE
                             SYNTAX        DisplayString
                             MAX-ACCESS    accessible-for-notify
                             STATUS        current
                             DESCRIPTION
                                "String that uniquely identifies the external sensor.
                                   Format is: SensorType,ChannelNumber,SensorSubtype,SerialNumber
                                   Example external temperature sensor: Temperature,,,AEI8160083
                                   Example external smoke detection sensor: onOff,2,contact,AEJ8160085
                                   Example outlet Current: rmsCurrent,,,
                                 "
                       ::= { info 38 }



lastUpgradeStatus            OBJECT-TYPE
                               SYNTAX     BITS{
                                                  mainController(0),
                                                  psoc1(1),
                                                  psoc2(2),
                                                  psoc3(3),
                                                  psoc4(4),
                                                  psoc5(5),
                                                  psoc6(6)
                                                        }
                                      MAX-ACCESS    read-only
                                      STATUS        current
                                      DESCRIPTION
                                          "A bit string  which indicates which the status of the last upgrade.
                                           A value of 1 for a bit position indicates that the corresponding upgrade failed.
                                           If all bits are zero,  then the upgrade succeeded;
                                            otherwise check lastUpgradeErrorDescription for further information.
"
                                      ::= { info 39 }


lastUpgradeTimestamp            OBJECT-TYPE
                               SYNTAX     DateAndTime
                                      MAX-ACCESS    read-only
                                      STATUS        current
                                      DESCRIPTION
                                          "The time when the last upgrade completed"
                                      ::= { info 40 }


lastUpgradeErrorDescription   OBJECT-TYPE
                             SYNTAX        DisplayString
                             MAX-ACCESS    read-only
                             STATUS        current
                             DESCRIPTION
                                "String that describes the upgrade errror.
                                 This is an empty string if the upgrade succeeded.
                                   Format is
                                      Failed PSOCs: 1[O:1,2,3-7];3[O:6-9,10-12]
                                      This indicates that upgrade of psocs 1 and 3 failed and
                                       psoc1 affects outlets 1,2, 3-7
                                       and psoc2 affects outlets 6-9,10-12
                                 "
                                    ::= { info 41 }


powerCIMStatus              OBJECT-TYPE
                             SYNTAX        PowerCIMStatusEnumeration
                             MAX-ACCESS    read-write
                             STATUS        current
                             DESCRIPTION
                                "The status of the Power CIM: on or off
                                 "
                                    ::= { info 42 }


measurementsPerLogEntry       OBJECT-TYPE
                                    SYNTAX        Integer32
                                    MAX-ACCESS    read-write
                                    STATUS        current
                                    DESCRIPTION
                                      "The number of measurements used for each entry in the log.
                                         1<= Value <= 200
                                         Default is 20
                                       This is related to dataLoggingInterval as shown below

                                           dataLoggingInterval   measurementsPerLogEntry
                                                3n                      n

                                      Example:  dataLoggingInterval  is 60, so every 60 seconds (or 20th sample)
                                                   data will be placed in the data log
                                                measurementsPerLogEntry is 20, so the data log sill store the minimum, average
                                                   and maximum of every 20 samples"
                                   ::= { info 43}

psocNumber       OBJECT-TYPE
                                    SYNTAX        Integer32
                                    MAX-ACCESS    accessible-for-notify
                                    STATUS        current
                                    DESCRIPTION
                                      "The psoc (Outlet Controller) number"
                                   ::= { info 44}

altitude       OBJECT-TYPE
                                    SYNTAX        Integer32(0..3000)
                                    MAX-ACCESS    read-write
                                    STATUS        current
                                    DESCRIPTION
                                      "The altitude (height above sea level) of the PDU in meters.
                                        0 <= Value <= 3000; default value is 0 meters "
                                   ::= { info 45}

configureAlerts    OBJECT-TYPE
                                      SYNTAX        DisplayString
                                      MAX-ACCESS    read-write
                                      STATUS        current
                                      DESCRIPTION
                                          "This is an operation. It has write-only semantics.
                                           GET operation will return the empty string.
                                           For SET operations, it configures alerts
                                           The format is a comma separated list of the following parameters.
                                                sensorClass, eventType, eventDirection, policyName
                                                   For sensorclass: use the SensorClass eumeration
                                                   For eventType: use the EventType enumeration
                                                   For eventDirection: use the EventDirection enumeration
                                                   For Policy Name: use the name of the policy; the Policy Name is case sensitive
                                           Note: setting this variable will overwrite the existing policy


                                            Example: if the External Temperature  upper non-critical threshold is either asserted and deasserted,
                                                       then  execute the policy named multiple destinations
                                                   the string would be
                                                    0,1,2,multiple destinations



                                            "
                                      ::= { info 46 }

fipsMode       OBJECT-TYPE
                                    SYNTAX        EnabledDisabledEnumeration
                                    MAX-ACCESS    read-write
                                    STATUS        current
                                    DESCRIPTION
                                      "The fips mode: either enabled or disabled.
                                       The mode can be set (changed) only if both of the following conditions hold
                                         a) the user is admin
                                         b) snmpv3 is being used.
                                       Changing this mode will result in a reboot of the PX
                                       When the PX is in FIPS mode, the follwing conditions hold.
                                         a) FIPS approved algorithms must be used
                                         b) snmp v1 & v2c are not supported
                                         b) snmp v3 must be used with AES and SHA
                                         c) https must be used; http is not supported
                                         d) Radius authentication is not supported
                                         e) Ldaps must be used; ldap is not supported
                                         f) ipmi v2.0 must be used
                                       "
                                   ::= { info 47}




synchronizeWithNTPServer OBJECT-TYPE
                                  SYNTAX          EnabledDisabledEnumeration
                                  MAX-ACCESS      read-write
                                  STATUS          current
                                  DESCRIPTION
                                      "Will time be obtained using NTP?
                                       Deafault is disabled, i.e. time will not be obtained from NTP servers."

                                  ::= { info 48 }

useDHCPProvidedNTPServer OBJECT-TYPE
                                  SYNTAX          EnabledDisabledEnumeration
                                  MAX-ACCESS      read-write
                                  STATUS          current
                                  DESCRIPTION
                                      "Will the NTP server addresses be provided by DHCP/BOOTP?
                                       This is used only if synchronizeWithNTPServer is enabled
                                       Default is enabled, i.e. DHCP provided NTP servers will be used "

                                  ::= { info 49 }


--   Corresponding InetAddressType objects and InetAddress objects must be consistent.
--     primaryNTPServerAddressType and primaryNTPServerAddress must be consistent
--     secondaryNTPServerAddressType and secondaryNTPServerAddress must be consistent

--    Attempts to set an InetAddress object to a value inconsistent with the associated InetAddressType
--       must fail with an inconsistentValue error.
--   Example:
--       Suppose  InetAddressType = ipv4 and InetAddress = 192.168.25.67
--       Setting InetAddress to www.xyz.com will return inconsistentValue error


--   When InetAddressType is changed to a type inconsistent with InetAddress, InetAddress may not display
--   the correct value until the format of InetAddress is changed to be consistent with InetAddressType
--   Example:
--      Suppose  InetAddressType = ipv4 and InetAddress = 192.168.25.67
--      InetAddressType is set to dns.
--      A GET operation on InetAddress may not display the correct value.
--      InetAddress is changed to www.xyz.com
--      A GET operation on InetAddress displays the correct value.

--   Recommended Approach to changing IP address representation.

--     1) First change InetAddressType to the correct type.
--     2) Next change InetAddress to a value consistent with the type.

--        Example: Change from IPv4 address to hostname
--         Intially: InetAddressType = ipv4
--                   InetAddress = 192.168.25.67
--         Change: InetAddressType = dns
--                 InetAddress = 192.67.29.36


primaryNTPServerAddressType OBJECT-TYPE
                                  SYNTAX          InetAddressType
                                  MAX-ACCESS      read-write
                                  STATUS          current
                                  DESCRIPTION
                                      "Represents the type of the corresponding instance
                                       of primaryNTPServerAddress object.


                                      "
                                  DEFVAL          { ipv4 }
                                  ::= { info 50 }

primaryNTPServerAddress     OBJECT-TYPE
                                 SYNTAX          InetAddress
                                 MAX-ACCESS      read-write
                                 STATUS          current
                                 DESCRIPTION
                                    "The address of the primary ntp server."
                                 ::= { info 51 }


secondaryNTPServerAddressType OBJECT-TYPE
                                  SYNTAX          InetAddressType
                                  MAX-ACCESS      read-write
                                  STATUS          current
                                  DESCRIPTION
                                      "Represents the type of the corresponding instance
                                       of secondaryNTPServerAddress object.
                                       Default is ipv4"

                                  ::= { info 52 }

secondaryNTPServerAddress     OBJECT-TYPE
                                 SYNTAX          InetAddress
                                 MAX-ACCESS      read-write
                                 STATUS          current
                                 DESCRIPTION
                                    "The address of the secondary ntp server."
                                 ::= { info 53 }





daylightSavingsTime      OBJECT-TYPE
                                  SYNTAX          EnabledDisabledEnumeration
                                  MAX-ACCESS      read-write
                                  STATUS          current
                                  DESCRIPTION
                                     "Is daylight savings time enabled?
                                      Default is disabled "

                                  ::= { info 55 }


thresholdValue  OBJECT-TYPE
                                     SYNTAX        DisplayString
                                     MAX-ACCESS    accessible-for-notify
                                     STATUS        current
                                     DESCRIPTION
                                         "The value of the threshold that has been triggered (or cleared).
                                          It is used in the thresholdAlarm trap for external numeric sensors only."
                                   ::= { info 56 }


sensorValue  OBJECT-TYPE
                                     SYNTAX        DisplayString
                                     MAX-ACCESS    accessible-for-notify
                                     STATUS        current
                                     DESCRIPTION
                                         "The sensor reading that triggered (or cleared) the threshold.
                                          It is used in the thresholdAlarm trap for external numeric sensors only."
                                   ::= { info 57 }




ipmiOverLAN       OBJECT-TYPE
                                    SYNTAX        EnabledDisabledEnumeration
                                    MAX-ACCESS    read-write
                                    STATUS        current
                                    DESCRIPTION
                                      "IPMI over LAN Mode: either enabled or disabled.
                                       It is strongly recommended that SNMPv3 be used to change the mode;
                                       SNMPv2c may also be used, but is not recommended.
                                       If SNMPv3 is used, then the change can be made only by users belonging to the Admin group.
                                       Changing the mode will result in a reboot of the PX.

                                       "
                                   ::= { info 58}







-- the inlets group

-- Implementation for managing the inlets

inletCount     OBJECT-TYPE
                SYNTAX        Integer32
                MAX-ACCESS    read-only
                STATUS        current
                DESCRIPTION
                    "The number of inlets present on this pdu."
                ::= { inlets 1 }


-- the inlets table

-- The inlets table contains information on the pdu's inlets.
-- It further provides functions for managing them.

inletTable     OBJECT-TYPE
                SYNTAX        SEQUENCE OF InletEntryStruct
                MAX-ACCESS    not-accessible
                STATUS        current
                DESCRIPTION
                    "A list of inlet entries. The number of
                     entries is given by the value of inletCount."
                ::= { inlets 2 }

inletEntry     OBJECT-TYPE
                SYNTAX        InletEntryStruct
                MAX-ACCESS    not-accessible
                STATUS        current
                DESCRIPTION
                    "An inlet entry containing objects for each inlet"
                INDEX         { inletIndex }
                ::= { inletTable 1 }

InletEntryStruct ::= SEQUENCE {  inletIndex                         Integer32,
                                 inletPoleCount                     Integer32,
                                 inletCurrentRating                 MilliAmps,
                                 inletCurrent                       MilliAmps,
                                 inletVoltage                       MilliVolts,
                                 inletActivePower                   Watts,
                                 inletApparentPower                 VoltAmps,
                                 inletPowerFactor                   PowerFactorPercentage,
                                 inletActiveEnergy                  WattHours,
                                 inletCurrentUnbalance              DisplayString,
                                 inletCurrentUpperWarning           MilliAmps,
                                 inletCurrentUpperCritical          MilliAmps,
                                 inletCurrentLowerWarning           MilliAmps,
                                 inletCurrentLowerCritical          MilliAmps,
                                 inletVoltageUpperWarning           MilliVolts,
                                 inletVoltageUpperCritical          MilliVolts,
                                 inletVoltageLowerWarning           MilliVolts,
                                 inletVoltageLowerCritical          MilliVolts,
                                 inletCurrentUnbalanceUpperCritical Percentage,
                                 inletCurrentUnbalanceUpperWarning  Percentage,
                                 inletCurrentHysteresis             Unsigned32,
                                 inletVoltageHysteresis             Unsigned32,
                                 inletCurrentUnbalanceHysteresis    Unsigned32
                              }

inletIndex                           OBJECT-TYPE
                                      SYNTAX        Integer32(1..256)
                                      MAX-ACCESS    not-accessible
                                      STATUS        current
                                      DESCRIPTION
                                          "A unique value for each inlet. Its value
                                           ranges between 1 and the value of inletCount."
                                      ::= { inletEntry 1 }

inletPoleCount     OBJECT-TYPE
                    SYNTAX        Integer32
                    MAX-ACCESS    read-only
                    STATUS        current
                    DESCRIPTION
                       "The number of poles for an inlet (1 for single phase, 3 for 3 phase Delta-wired,
                         4 for 3 phase WYE wired)."
                    ::= { inletEntry 3 }

inletCurrentRating                   OBJECT-TYPE
                                      SYNTAX        MilliAmps
                                      MAX-ACCESS    read-only
                                      STATUS        current
                                      DESCRIPTION
                                          "The input current Rating"
                                      ::= { inletEntry 4}

inletCurrent                         OBJECT-TYPE
                                      SYNTAX        MilliAmps
                                      MAX-ACCESS    read-only
                                      STATUS        current
                                      DESCRIPTION
                                          "A unique value for the current sensor
                                           attached to the inlet.  This value is
                                           reported in milliamps (1/1000th of an amp).
                                           This OID does not apply to 3 phase systems;
					   a value of 0 will be reported for same."
                                      ::= { inletEntry 7 }

inletVoltage                         OBJECT-TYPE
                                      SYNTAX        MilliVolts
                                      MAX-ACCESS    read-only
                                      STATUS        current
                                      DESCRIPTION
                                          "A unique value for the voltage sensor
                                           attached to the intlet.This value is
                                           reported in millivolts (1/1000th of a volt).
                                           This OID does not apply to 3 phase systems;
					   a value of 0 will be reported for same."
                                      ::= { inletEntry 8 }

inletActivePower                     OBJECT-TYPE
                                      SYNTAX        Watts
                                      MAX-ACCESS    read-only
                                      STATUS        current
                                      DESCRIPTION
                                          "The active power for the inlet
                                           This value is reported in Watts."
                                      ::= { inletEntry 9 }

inletApparentPower                   OBJECT-TYPE
                                      SYNTAX        VoltAmps
                                      MAX-ACCESS    read-only
                                      STATUS        current
                                      DESCRIPTION
                                          "The apparent power for the inlet.
                                           This value is reported in Volt-Amps"
                                      ::= { inletEntry 10 }

inletPowerFactor                     OBJECT-TYPE
                                      SYNTAX        PowerFactorPercentage
                                      MAX-ACCESS    read-only
                                      STATUS        current
                                      DESCRIPTION
                                          "A unique value for the power factor
                                           of the inlet. The reading represents a
                                           percentage in the range of 0% to 100%."
                                      ::= { inletEntry 11 }

inletActiveEnergy                         OBJECT-TYPE
                                      SYNTAX        WattHours
                                      MAX-ACCESS    read-only
                                      STATUS        current
                                      DESCRIPTION
                                          "This object has an invalid value if outletEnergySupport = 'No';
                                           In all other cases, it is the value of the cumulative active energy for this inlet.
                                           This value is reported in WattHours"
                                      ::= { inletEntry 12 }

inletCurrentUnbalance         OBJECT-TYPE
                         SYNTAX        DisplayString
                         MAX-ACCESS    read-only
                         STATUS        current
                         DESCRIPTION
                            "A string displaying the current unbalance in percent.
                             It will have the value NA if
                              the feature is disabled,
                              the PX is not a 3-phase unit,or
                              the average of the line currents is zero"
                         ::= { inletEntry 15 }

inletCurrentUpperWarning             OBJECT-TYPE
                                      SYNTAX        MilliAmps
                                      MAX-ACCESS    read-write
                                      STATUS        current
                                      DESCRIPTION
                                           "The value of the upper warning (non-critical)
                                            current threshold for the inlet. This value is
                                           reported in milliamps (1/1000th of an amp)"
                                      ::= { inletEntry 20 }

inletCurrentUpperCritical            OBJECT-TYPE
                                      SYNTAX        MilliAmps
                                      MAX-ACCESS    read-write
                                      STATUS        current
                                      DESCRIPTION
                                           "The value of the upper critical current
                                            threshold for the inlet. This value is
                                           reported in milliamps (1/1000th of an amp)"
                                      ::= { inletEntry 21 }


inletCurrentLowerWarning             OBJECT-TYPE
                                      SYNTAX        MilliAmps
                                      MAX-ACCESS    read-write
                                      STATUS        current
                                      DESCRIPTION
                                           "The value of the lower warning (non-critical)
                                            current threshold for the inlet. This value is
                                           reported in milliamps (1/1000th of an amp).
                                           This OID is valid for inline meter PDU's. only"
                                      ::= { inletEntry 22 }

inletCurrentLowerCritical            OBJECT-TYPE
                                      SYNTAX        MilliAmps
                                      MAX-ACCESS    read-write
                                      STATUS        current
                                      DESCRIPTION
                                           "The value of the lower critical current
                                            threshold for the inlet. This value is
                                           reported in milliamps (1/1000th of an amp).
                                           This OID is valid for inline meter PDU's only."
                                      ::= { inletEntry 23 }

inletVoltageUpperWarning             OBJECT-TYPE
                                      SYNTAX        MilliVolts
                                      MAX-ACCESS    read-write
                                      STATUS        current
                                      DESCRIPTION
                                           "The value of the upper warning (non-critical)
                                            current threshold for the inlet. This value is
                                            reported in millivolts (1/1000th of a volt)"
                                      ::= { inletEntry 24 }

inletVoltageUpperCritical            OBJECT-TYPE
                                      SYNTAX        MilliVolts
                                      MAX-ACCESS    read-write
                                      STATUS        current
                                      DESCRIPTION
                                           "The value of the upper critical current
                                            threshold for the inlet. This value is
                                           reported in millivolts (1/1000th of a volt)"
                                      ::= { inletEntry 25 }

inletVoltageLowerWarning             OBJECT-TYPE
                                      SYNTAX        MilliVolts
                                      MAX-ACCESS    read-write
                                      STATUS        current
                                      DESCRIPTION
                                           "The value of the lower warning (non-critical)
                                            current threshold for the inlet. This value is
                                            reported in millivolts (1/1000th of a volt)"
                                      ::= { inletEntry 26 }

inletVoltageLowerCritical            OBJECT-TYPE
                                      SYNTAX        MilliVolts
                                      MAX-ACCESS    read-write
                                      STATUS        current
                                      DESCRIPTION
                                           "The value of the lower critical current
                                            threshold for the inlet. This value is
                                            reported in millivolts (1/1000th of a volt)"
                                      ::= { inletEntry 27 }

inletCurrentUnbalanceUpperCritical     OBJECT-TYPE
                                     SYNTAX        Percentage
                                     MAX-ACCESS    read-write
                                     STATUS        current
                                     DESCRIPTION
                                            "The value of the upper critical current Unbalance threshold."
                                     ::= { inletEntry 28 }

inletCurrentUnbalanceUpperWarning     OBJECT-TYPE
                                     SYNTAX        Percentage
                                     MAX-ACCESS    read-write
                                     STATUS        current
                                     DESCRIPTION
                                            "The value of the upper warning current Unbalance threshold."
                                     ::= { inletEntry 29 }


inletCurrentHysteresis        OBJECT-TYPE
                                      SYNTAX        Unsigned32
                                      MAX-ACCESS    read-write
                                      STATUS        current
                                      DESCRIPTION
                                          "The hysteresis used for deassertions. This value is
                                           reported in milliamps (1/1000th of an amp)"
                                      ::= { inletEntry 30 }


inletVoltageHysteresis        OBJECT-TYPE
                                      SYNTAX        Unsigned32
                                      MAX-ACCESS    read-write
                                      STATUS        current
                                      DESCRIPTION
                                          "The hysteresis used for deassertions. This value is
                                           reported in millivolts (1/1000th of a volt)"
                                      ::= { inletEntry 31 }

inletCurrentUnbalanceHysteresis        OBJECT-TYPE
                                      SYNTAX        Unsigned32
                                      MAX-ACCESS    read-write
                                      STATUS        current
                                      DESCRIPTION
                                          "The hysteresis used for deassertions. This value is
                                           reported in percent"
                                      ::= { inletEntry 32 }

-- the  inletPole group

-- Implementation for  Line data

-- the inletPole table

-- The inletPoleTable table contains information on the poles for an inlet

inletPoleTable     OBJECT-TYPE
                    SYNTAX        SEQUENCE OF InletPoleEntryStruct
                    MAX-ACCESS    not-accessible
                    STATUS        current
                    DESCRIPTION
                        "A list of line input entries. The number of entries is given by
                         the value of inletTable(inletIndex).inletPoleCount."
                    ::= { inletPole 2 }

inletPoleEntry     OBJECT-TYPE
                    SYNTAX        InletPoleEntryStruct
                    MAX-ACCESS    not-accessible
                    STATUS        current
                    DESCRIPTION
                        "An entry in the data log containing  input line values
                        for a particular input line."
                    INDEX         { inletIndex,inletPoleIndex }
                    ::= { inletPoleTable 1 }

InletPoleEntryStruct ::= SEQUENCE {       inletPoleIndex                     Integer32,
                                          inletPoleLabel                     DisplayString,
                                          inletPoleCurrent                   MilliAmps,
                                          inletPoleVoltage                   MilliVolts,
                                          inletPoleMaxCurrent                MilliAmps,
                                          inletPoleActivePower               Watts,
                                          inletPoleApparentPower             VoltAmps,
                                          inletPolePowerFactor               PowerFactorPercentage,
                                          inletPoleActiveEnergy              WattHours
                                          }

inletPoleIndex                    OBJECT-TYPE
                                   SYNTAX        Integer32(1..256)
                                   MAX-ACCESS    not-accessible
                                   STATUS        current
                                   DESCRIPTION
                                       "A unique value for each line input. Its value
                                        ranges between 1 and of inletTable(inletIndex).inletPoleCount."
                                   ::= { inletPoleEntry 1 }


inletPoleLabel                OBJECT-TYPE
                                   SYNTAX      DisplayString
                                   MAX-ACCESS    read-only
                                   STATUS        current
                                   DESCRIPTION
                                       "A string identifying the Line
                                          For Single Phase: L1
                                          For 3phase Delta wired outlets: L1, L2, L3
                                          For 3phase WYE Wired Outlets: L1, L2, L3"
                                   ::= { inletPoleEntry 2 }

inletPoleCurrent                          OBJECT-TYPE
                                   SYNTAX        MilliAmps
                                   MAX-ACCESS    read-only
                                   STATUS        current
                                   DESCRIPTION
                                       "The value of the line current reported in MilliAmps.
                                         inletPoleIndex = 1; For Single Phase, Input Line Current; For 3-phase, L1 Current
                                         inletPoleIndex = 2; For 3-phase, L2 Current
                                         inletPoleIndex = 3; For 3-phase, L3 Current"
                                   ::= { inletPoleEntry 3 }

inletPoleVoltage                          OBJECT-TYPE
                                   SYNTAX        MilliVolts
                                   MAX-ACCESS    read-only
                                   STATUS        current
                                   DESCRIPTION
                                       "The value of the line-line voltage reported in MilliVolts.
                                          inletPoleIndex = 1; Single Phase Input Line Voltage
                                                             3-phase, L1-L2 Voltage or L1-N voltage
                                          inletPoleIndex = 2; 3-phase L2-L3 Voltage or L2-N voltage
                                          inletPoleaIndex = 3; 3-phase L3-L1 Voltage or L3-N voltage"
                                   ::= { inletPoleEntry 4 }

inletPoleMaxCurrent                      OBJECT-TYPE
                                      SYNTAX        MilliAmps
                                      MAX-ACCESS    read-only
                                      STATUS        current
                                      DESCRIPTION
                                           "This object has an invalid value for a single-phase PDU.
                                            If inletPoleCount = 1, then the value is invalid;
                                            In all other cases, it is the value of the max. current sensor
                                           attached to the inlet Pole.  This value is
                                           reported in milliamps (1/1000th of an amp)"
                                      ::= { inletPoleEntry 5 }

inletPoleActivePower                     OBJECT-TYPE
                                      SYNTAX        Watts
                                      MAX-ACCESS    read-only
                                      STATUS        current
                                      DESCRIPTION
                                          "This object has a valid value only for inline meters.
                                            If inlineMeter = 'No', then the value is invalid;
                                           In all other cases, it is the active power for the line/pole.
                                           The value is reported in Watts."
                                      ::= { inletPoleEntry 7 }

inletPoleApparentPower                   OBJECT-TYPE
                                      SYNTAX        VoltAmps
                                      MAX-ACCESS    read-only
                                      STATUS        current
                                      DESCRIPTION
                                          "This object has a valid value only for inline meters.
                                            If inlineMeter = 'No', then the value is invalid;
                                           In all other cases, it is the apparent power for the line/pole.
                                           The value is reported in Volt-Amps"
                                      ::= { inletPoleEntry 8 }

inletPolePowerFactor                     OBJECT-TYPE
                                      SYNTAX        PowerFactorPercentage
                                      MAX-ACCESS    read-only
                                      STATUS        current
                                      DESCRIPTION
                                          "This object has a valid value only for inline meters.
                                            If inlineMeter = 'No', then the value is invalid;
                                           In all other cases, it is the power factor for the line/pole
                                           The reading represents a percentage in the range of 0% to 100%."
                                      ::= { inletPoleEntry 9 }

inletPoleActiveEnergy                   OBJECT-TYPE
                                      SYNTAX        WattHours
                                      MAX-ACCESS    read-only
                                      STATUS        current
                                      DESCRIPTION
                                          "This object has a valid value only for inline meters.
                                            If inlineMeter = 'No', then the value is invalid;
                                           In all other cases, it is the cumulative active energy for the line/pole.
                                           The value is reported in WattHours"
                                      ::= { inletPoleEntry 11 }


-- the outlets group

-- Implementation for managing the outlets

outletCount     OBJECT-TYPE
                SYNTAX        Integer32
                MAX-ACCESS    read-only
                STATUS        current
                DESCRIPTION
                    "The number of outlets (regardless of
                     their current state) present on this pdu."
                ::= { outlets 1 }

-- the outlets table

-- The outlets table contains information on the pdu's outlets.
-- It further provides functions for managing them.

outletTable     OBJECT-TYPE
                SYNTAX        SEQUENCE OF OutletEntryStruct
                MAX-ACCESS    not-accessible
                STATUS        current
                DESCRIPTION
                    "A list of outlet entries. The number of
                     entries is given by the value of outletCount."
                ::= { outlets 2 }

outletEntry     OBJECT-TYPE
                SYNTAX        OutletEntryStruct
                MAX-ACCESS    not-accessible
                STATUS        current
                DESCRIPTION
                    "An outlet entry containing objects at the
                     for a particular outlet."
                INDEX         { outletIndex }
                ::= { outletTable 1 }

OutletEntryStruct ::= SEQUENCE { outletIndex                        Integer32,
                                 outletLabel                        DisplayString,
                                 outletOperationalState             INTEGER,
                                 outletCurrent                      MilliAmps,
                                 outletMaxCurrent                   MilliAmps,
                                 outletVoltage                      MilliVolts,
                                 outletActivePower                  Watts,
                                 outletApparentPower                VoltAmps,
                                 outletPowerFactor                  PowerFactorPercentage,
                                 outletCurrentUpperWarning          MilliAmps,
                                 outletCurrentUpperCritical         MilliAmps,
                                 outletCurrentLowerWarning          MilliAmps,
                                 outletCurrentLowerCritical         MilliAmps,
                                 outletCurrentHysteresis            Unsigned32,
                                 outletCurrentRating                MilliAmps,
                                 outletWattHours                    WattHours  }

outletIndex                           OBJECT-TYPE
                                      SYNTAX        Integer32(1..256)
                                      MAX-ACCESS    not-accessible
                                      STATUS        current
                                      DESCRIPTION
                                          "A unique value for each outlet. Its value
                                           ranges between 1 and the value of outletCount."
                                      ::= { outletEntry 1 }

outletLabel                           OBJECT-TYPE
                                      SYNTAX        DisplayString
                                      MAX-ACCESS    read-write
                                      STATUS        current
                                      DESCRIPTION
                                          "A textual string containing information
                                           about the outlet."
                                      ::= { outletEntry 2 }


outletOperationalState                OBJECT-TYPE
                                      SYNTAX        INTEGER { error(-1),
                                                              off(0),
                                                              on(1),
                                                              cycling(2) }
                                      MAX-ACCESS    read-write
                                      STATUS        current
                                      DESCRIPTION
                                          "A value for each outlet which describes the
                                           operational state of the outlet. It is also
                                           used to set the operational state of the outlet"
                                      ::= { outletEntry 3 }

outletCurrent                         OBJECT-TYPE
                                      SYNTAX        MilliAmps
                                      MAX-ACCESS    read-only
                                      STATUS        current
                                      DESCRIPTION
                                          "A unique value for the current sensor
                                           attached to the outlet.  This value is
                                           reported in milliamps (1/1000th of an amp)"
                                      ::= { outletEntry 4 }

outletMaxCurrent                      OBJECT-TYPE
                                      SYNTAX        MilliAmps
                                      MAX-ACCESS    read-only
                                      STATUS        current
                                      DESCRIPTION
                                           "A unique value for the max. current sensor
                                           attached to the outlet.  This value is
                                           reported in milliamps (1/1000th of an amp)"
                                      ::= { outletEntry 5 }

outletVoltage                         OBJECT-TYPE
                                      SYNTAX        MilliVolts
                                      MAX-ACCESS    read-only
                                      STATUS        current
                                      DESCRIPTION
                                          "A unique value for the voltage sensor
                                           attached to the outlet.This value is
                                           reported in millivolts (1/1000th of a volt)"
                                      ::= { outletEntry 6 }

outletActivePower                     OBJECT-TYPE
                                      SYNTAX        Watts
                                      MAX-ACCESS    read-only
                                      STATUS        current
                                      DESCRIPTION
                                          "A unique value for the active power sensor
                                           attached to the outlet.  This value is
                                           reported in Watts."
                                      ::= { outletEntry 7 }

outletApparentPower                   OBJECT-TYPE
                                      SYNTAX        VoltAmps
                                      MAX-ACCESS    read-only
                                      STATUS        current
                                      DESCRIPTION
                                          "A unique value for the apparent power sensor
                                           attached to the outlet.  This value is
                                           reported in Volt-Amps"
                                      ::= { outletEntry 8 }

outletPowerFactor                     OBJECT-TYPE
                                      SYNTAX        PowerFactorPercentage
                                      MAX-ACCESS    read-only
                                      STATUS        current
                                      DESCRIPTION
                                          "A unique value for the power factor
                                           of the outlet. The reading represents a
                                           percentage in the range of 0% to 100%."
                                      ::= { outletEntry 9 }

outletCurrentUpperWarning             OBJECT-TYPE
                                      SYNTAX        MilliAmps
                                      MAX-ACCESS    read-write
                                      STATUS        current
                                      DESCRIPTION
                                           "The value of the upper warning (non-critical)
                                            current threshold for the outlet. This value is
                                           reported in milliamps (1/1000th of an amp)"
                                      ::= { outletEntry 20 }

outletCurrentUpperCritical            OBJECT-TYPE
                                      SYNTAX        MilliAmps
                                      MAX-ACCESS    read-write
                                      STATUS        current
                                      DESCRIPTION
                                           "The value of the upper critical current
                                            threshold for the outlet. This value is
                                           reported in milliamps (1/1000th of an amp)"
                                      ::= { outletEntry 21 }


outletCurrentLowerWarning             OBJECT-TYPE
                                      SYNTAX        MilliAmps
                                      MAX-ACCESS    read-write
                                      STATUS        current
                                      DESCRIPTION
                                           "The value of the lower warning (non-critical)
                                            current threshold for the outlet. This value is
                                           reported in milliamps (1/1000th of an amp)"
                                      ::= { outletEntry 22 }

outletCurrentLowerCritical            OBJECT-TYPE
                                      SYNTAX        MilliAmps
                                      MAX-ACCESS    read-write
                                      STATUS        current
                                      DESCRIPTION
                                           "The value of the lower critical current
                                            threshold for the outlet. This value is
                                           reported in milliamps (1/1000th of an amp)"
                                      ::= { outletEntry 23 }

outletCurrentHysteresis        OBJECT-TYPE
                                      SYNTAX        Unsigned32
                                      MAX-ACCESS    read-write
                                      STATUS        current
                                      DESCRIPTION
                                          "The hysteresis used for deassertions. This value is
                                           reported in milliamps (1/1000th of an amp)"
                                      ::= { outletEntry 24 }

outletCurrentRating                   OBJECT-TYPE
                                      SYNTAX        MilliAmps
                                      MAX-ACCESS    read-only
                                      STATUS        current
                                      DESCRIPTION
                                          "The current rating of the outlet. This value is
                                           reported in milliamps (1/1000th of an amp)"
                                      ::= { outletEntry 30 }

outletWattHours                         OBJECT-TYPE
                                      SYNTAX        WattHours
                                      MAX-ACCESS    read-only
                                      STATUS        current
                                      DESCRIPTION
                                          "The value of the cumulative active energy for this outlet.
                                           This value is reported in WattHours"
                                      ::= { outletEntry 31 }

-- the unitReadings group

-- The unitReadings group contains sensor reading values
-- for the PDU unit as a whole

unitCurrent               OBJECT-TYPE
                          SYNTAX      MilliAmps
                          MAX-ACCESS  read-only
                          STATUS      deprecated
                          DESCRIPTION
                              "The value for the unit's current sensor in millamps.This object is deprecated
                               in favour of lineCurrent corresponding to lineCurrentLabel = L1"
                          ::= { unitReadings 1 }

unitVoltage               OBJECT-TYPE
                          SYNTAX      MilliVolts
                          MAX-ACCESS  read-only
                          STATUS      deprecated
                          DESCRIPTION
                              "The value for the unit's voltage sensor in millivolts.This object is deprecated
                               in favour of lineVoltage corresponding to lineVoltageLabel = L1"
                          ::= { unitReadings 2 }

unitActivePower         OBJECT-TYPE
                          SYNTAX      Watts
                          MAX-ACCESS  read-only
                          STATUS      deprecated
                          DESCRIPTION
                              "The value for the unit's active power in watts.This object is deprecated
                               in favour of inletTable.inletActivePower"
                          ::= { unitReadings 3 }

unitApparentPower         OBJECT-TYPE
                          SYNTAX      VoltAmps
                          MAX-ACCESS  read-only
                          STATUS      deprecated
                          DESCRIPTION
                              "The value for the unit's apparent power in volt-amps. This object is deprecated
                               in favour of inletTable.inletApparentPower"
                          ::= { unitReadings 4 }

unitCpuTemp               OBJECT-TYPE
                          SYNTAX      TenthDegreesCelsius
                          MAX-ACCESS  read-only
                          STATUS      current
                          DESCRIPTION
                              "The value for the unit's CPU temperature sensor in tenth degrees celsius."
                          ::= { unitReadings 5 }

unitVoltageLowerWarning   OBJECT-TYPE
                          SYNTAX        MilliVolts
                          MAX-ACCESS    read-write
                          STATUS        deprecated
                          DESCRIPTION
                              "The value of the lower warning (non-critical) unit level voltage threshold.This object is deprecated
                               in favour of unitOrLineVoltageLowerWarning"
                          ::= { unitReadings 60 }

unitVoltageLowerCritical  OBJECT-TYPE
                          SYNTAX        MilliVolts
                          MAX-ACCESS    read-write
                          STATUS        deprecated
                          DESCRIPTION
                              "The value of the lower critical unit level voltage threshold.This object is deprecated
                               in favour of unitOrLineVoltageLowerCritical"
                          ::= { unitReadings 61 }

unitVoltageUpperWarning  OBJECT-TYPE
                          SYNTAX        MilliVolts
                          MAX-ACCESS    read-write
                          STATUS        deprecated
                          DESCRIPTION
                              "The value of the upper warning (non-critical) unit level voltage threshold.This object is deprecated
                               in favour of unitOrLineVoltageUpperWarning"
                          ::= { unitReadings 62 }

unitVoltageUpperCritical  OBJECT-TYPE
                          SYNTAX        MilliVolts
                          MAX-ACCESS    read-write
                          STATUS        deprecated
                          DESCRIPTION
                              "The value of the upper critical unit level voltage threshold.This object is deprecated
                               in favour of unitOrLineVoltageUpperCritical"
                          ::= { unitReadings 63 }

unitCurrentUpperWarning   OBJECT-TYPE
                          SYNTAX        MilliAmps
                          MAX-ACCESS    read-write
                          STATUS        deprecated
                          DESCRIPTION
                              "The value of the upper warning (non-critical) unit level current threshold.This object is deprecated
                               in favour of unitOrLineCurrentUpperWarning"
                          ::= { unitReadings 70 }

unitCurrentUpperCritical  OBJECT-TYPE
                          SYNTAX        MilliAmps
                          MAX-ACCESS    read-only
                          STATUS        deprecated
                          DESCRIPTION
                              "The value of the upper critical unit level current threshold.  NOTE:  This
                               particular threshold is NOT settable. This object is deprecated
                               in favour of unitOrLineCurrentUpperCritica"
                          ::= { unitReadings 71 }

unitOrLineVoltageLowerWarning   OBJECT-TYPE
                          SYNTAX        MilliVolts
                          MAX-ACCESS    read-write
                          STATUS        current
                          DESCRIPTION
                              "The value of the lower warning (non-critical) unit level voltage threshold."
                          ::= { unitReadings 90 }

unitOrLineVoltageLowerCritical  OBJECT-TYPE
                          SYNTAX        MilliVolts
                          MAX-ACCESS    read-write
                          STATUS        current
                          DESCRIPTION
                              "The value of the lower critical unit level voltage threshold."
                          ::= { unitReadings 91 }

unitOrLineVoltageUpperWarning  OBJECT-TYPE
                          SYNTAX        MilliVolts
                          MAX-ACCESS    read-write
                          STATUS        current
                          DESCRIPTION
                              "The value of the upper warning (non-critical) unit level voltage"
                          ::= { unitReadings 92 }

unitOrLineVoltageUpperCritical  OBJECT-TYPE
                          SYNTAX        MilliVolts
                          MAX-ACCESS    read-write
                          STATUS        current
                          DESCRIPTION
                              "The value of the upper critical unit level voltage threshold."
                          ::= { unitReadings 93 }

unitOrLineCurrentUpperWarning   OBJECT-TYPE
                          SYNTAX        MilliAmps
                          MAX-ACCESS    read-write
                          STATUS        current
                          DESCRIPTION
                              "The value of the upper warning (non-critical) unit level current threshold"
                          ::= { unitReadings 94 }

unitOrLineCurrentUpperCritical  OBJECT-TYPE
                          SYNTAX        MilliAmps
                          MAX-ACCESS    read-write
                          STATUS        current
                          DESCRIPTION
                              "The value of the upper critical unit level current threshold. "
                          ::= { unitReadings 95 }

neutralCurrentUpperWarning   OBJECT-TYPE
                          SYNTAX        MilliAmps
                          MAX-ACCESS    read-write
                          STATUS        current
                          DESCRIPTION
                              "This object has an invalid value if inletPoleCount is not equal to 4.
                               If inletPoleCount = 4, then it is the value of the upper warning (non-critical) threshold
                               for the neutral current"
                          ::= { unitReadings 96 }

neutralCurrentUpperCritical  OBJECT-TYPE
                          SYNTAX        MilliAmps
                          MAX-ACCESS    read-write
                          STATUS        current
                          DESCRIPTION
                              "This object has an invalid value if inletPoleCount is not equal to 4.
                               If inletPoleCount = 4, then it is the value of the upper critical threshold
                               for the neutral current."
                          ::= { unitReadings 97 }

unitTempLowerWarning      OBJECT-TYPE
                          SYNTAX        DegreesCelsius
                          MAX-ACCESS    read-write
                          STATUS        current
                          DESCRIPTION
                              "The value of the lower warning (non-critical) unit level temperature threshold."
                          ::= { unitReadings 80 }

unitTempLowerCritical     OBJECT-TYPE
                          SYNTAX       	DegreesCelsius
                          MAX-ACCESS    read-write
                          STATUS        current
                          DESCRIPTION
                              "The value of the lower critical unit level temperature threshold."
                          ::= { unitReadings 81 }

unitTempUpperWarning      OBJECT-TYPE
                          SYNTAX        DegreesCelsius
                          MAX-ACCESS    read-write
                          STATUS        current
                          DESCRIPTION
                              "The value of the upper warning (non-critical) unit level temperature threshold."
                          ::= { unitReadings 82 }

unitTempUpperCritical     OBJECT-TYPE
                          SYNTAX        DegreesCelsius
                          MAX-ACCESS    read-write
                          STATUS        current
                          DESCRIPTION
                              "The value of the upper critical unit level temperature threshold."
                          ::= { unitReadings 83 }

currentUnbalance         OBJECT-TYPE
                         SYNTAX        DisplayString
                         MAX-ACCESS    read-only
                         STATUS        current
                         DESCRIPTION
                            "A string displaying the current unbalance in percent.
                             It will have the value NA if
                              the PX is not a 3-phase unit (inletPoleCount = 1),or
                              the feature is disabled (currentUnbalanceSupport = 'No'), or
                              the average of the line currents is zero (inletPoleCurrent = 0 for 1 <= inlePoleIndex <= 3)"
                         ::= { unitReadings 84 }

currentUnbalanceUpperWarning      OBJECT-TYPE
                          SYNTAX        Percentage
                          MAX-ACCESS    read-write
                          STATUS        current
                          DESCRIPTION
                              "The value of the upper warning (non-critical) current unbalance threshold."
                          ::= { unitReadings 85 }

currentUnbalanceUpperCritical     OBJECT-TYPE
                          SYNTAX        Percentage
                          MAX-ACCESS    read-write
                          STATUS        current
                          DESCRIPTION
                              "The value of the upper critical current Unbalance threshold."
                          ::= { unitReadings 86 }

unitOrLineCurrentHysteresis      OBJECT-TYPE
                                      SYNTAX        Unsigned32
                                      MAX-ACCESS    read-write
                                      STATUS        current
                                      DESCRIPTION
                                          "The hysteresis used for deassertions. This value is
                                           reported in milliamps (1/1000th of an amp)"
                                      ::= { unitReadings 98 }

unitOrLineVoltageHysteresis      OBJECT-TYPE
                                      SYNTAX        Unsigned32
                                      MAX-ACCESS    read-write
                                      STATUS        current
                                      DESCRIPTION
                                          "The hysteresis used for deassertions. This value is
                                           reported in millivolts (1/1000th of a volt)"
                                      ::= { unitReadings 99 }



unitTempHysteresis             OBJECT-TYPE
                                      SYNTAX        Unsigned32
                                      MAX-ACCESS    read-write
                                      STATUS        current
                                      DESCRIPTION
                                          "The hysteresis used for deassertions
                                           "
                                      ::= { unitReadings 100 }


currentUnbalanceHysteresis             OBJECT-TYPE
                                      SYNTAX        Unsigned32
                                      MAX-ACCESS    read-write
                                      STATUS        current
                                      DESCRIPTION
                                          "The hysteresis used for deassertions
                                           "
                                      ::= { unitReadings 101 }

-- the externalTemperature group

-- Implementation for managing external temperature sensors

tempSensorCount     OBJECT-TYPE
                    SYNTAX        Integer32
                    MAX-ACCESS    read-only
                    STATUS        deprecated
                    DESCRIPTION
                       "The number of external temperature sensors (regardless of
                         their current state) present on this pdu.
                         This is deprecated in favor of externalSensors"
                    ::= { environmental 1 }

-- the temperature sensors table

-- The tempSensorTable table contains information on the pdu's external temperature sensors.

tempSensorTable     OBJECT-TYPE
                    SYNTAX        SEQUENCE OF TempSensorEntryStruct
                    MAX-ACCESS    not-accessible
                    STATUS        deprecated
                    DESCRIPTION
                        "A list of temperature sensor entries. The number of
                         entries is given by the value of tempSensorCount.
                         This is deprecated in favor of externalSensors"
                    ::= { environmental 2 }

tempSensorEntry     OBJECT-TYPE
                    SYNTAX        TempSensorEntryStruct
                    MAX-ACCESS    not-accessible
                    STATUS        deprecated
                    DESCRIPTION
                        "An entry containing sensor reading and threshold
                        settings for a particular temperature sensor.
                         This is deprecated in favor of externalSensors"
                    INDEX         { tempSensorIndex }
                    ::= { tempSensorTable 1 }

TempSensorEntryStruct ::= SEQUENCE { tempSensorIndex                Integer32,
                                 tempSensorLabel                    DisplayString,
                                 temperature                        TenthDegreesCelsius,
                                 tempLowerWarning                   DegreesCelsius,
                                 tempUpperWarning                   DegreesCelsius,
                                 tempLowerCritical                  DegreesCelsius,
                                 tempUpperCritical                  DegreesCelsius,
                                 tempXCoordinate                    DisplayString,
                                 tempYCoordinate                    DisplayString,
                                 tempZCoordinate                   DisplayString}

tempSensorIndex                    OBJECT-TYPE
                                   SYNTAX        Integer32(1..256)
                                   MAX-ACCESS    not-accessible
                                   STATUS        deprecated
                                   DESCRIPTION
                                       "A unique value for each temperature sensor. Its value
                                        ranges between 1 and tempSensorCount.
                                        This is deprecated in favor of externalSensors"
                                   ::= { tempSensorEntry 1 }

tempSensorLabel                   OBJECT-TYPE
                                   SYNTAX        DisplayString
                                   MAX-ACCESS    read-write
                                   STATUS        deprecated
                                   DESCRIPTION
                                       "A settable human-readable label for the external temperature
                                       sensor.  One possible use for this label is to convey sensor
                                       location.
                                        This is deprecated in favor of externalSensors"
                                   ::= { tempSensorEntry 2 }

temperature                        OBJECT-TYPE
                                   SYNTAX        TenthDegreesCelsius
                                   MAX-ACCESS    read-only
                                   STATUS        deprecated
                                   DESCRIPTION
                                       "The value of the external temperature sensor reported
                                       in tenth degrees celsius.
                                        This is deprecated in favor of externalSensors"
                                   ::= { tempSensorEntry 3 }

tempLowerWarning       OBJECT-TYPE
                                   SYNTAX        DegreesCelsius
                                   MAX-ACCESS    read-write
                                   STATUS        deprecated
                                   DESCRIPTION
                                       "The value of the lower warning (non-critical) threshold.
                                         This is deprecated in favor of externalSensors"
                                   ::= { tempSensorEntry 4 }

tempUpperWarning       OBJECT-TYPE
                                   SYNTAX        DegreesCelsius
                                   MAX-ACCESS    read-write
                                   STATUS        deprecated
                                   DESCRIPTION
                                       "The value of the upper warning (non-critical) threshold.
                                         This is deprecated in favor of externalSensors"
                                   ::= { tempSensorEntry 5 }

tempLowerCritical         OBJECT-TYPE
                                   SYNTAX        DegreesCelsius
                                   MAX-ACCESS    read-write
                                   STATUS        deprecated
                                   DESCRIPTION
                                       "The value of the lower critical threshold.
                                          This is deprecated in favor of externalSensors"
                                   ::= { tempSensorEntry 6 }

tempUpperCritical          OBJECT-TYPE
                                   SYNTAX        DegreesCelsius
                                   MAX-ACCESS    read-write
                                   STATUS        deprecated
                                   DESCRIPTION
                                       "The value of the upper critical threshold.
                                         This is deprecated in favor of externalSensors"
                                   ::= { tempSensorEntry 7 }

tempXCoordinate            OBJECT-TYPE
                                   SYNTAX        DisplayString
                                   MAX-ACCESS    read-write
                                   STATUS        deprecated
                                   DESCRIPTION
                                       "The value of X coordinate in freeform
                                         with number of characters  <= 24
                                         This is deprecated in favor of externalSensors"
                                   ::= { tempSensorEntry 8 }

tempYCoordinate            OBJECT-TYPE
                                   SYNTAX        DisplayString
                                   MAX-ACCESS    read-write
                                   STATUS        deprecated
                                   DESCRIPTION
                                       "The value of Y coordinate in freeform
                                         with number of characters  <= 24
                                         This is deprecated in favor of externalSensors"
                                   ::= { tempSensorEntry 9 }

tempZCoordinate            OBJECT-TYPE
                                   SYNTAX        DisplayString
                                   MAX-ACCESS    read-write
                                   STATUS        deprecated
                                   DESCRIPTION
                                       "The value of Z coordinate in one of two formats:
                                          either freeform with  number of characters  <= 24
                                         or in Z units so that 0 =< integer value  <= 60
                                          This is deprecated in favor of externalSensors"
                                   ::= { tempSensorEntry 10 }

-- the externalHumidity group

-- Implementation for managing external humidity sensors

humiditySensorCount     OBJECT-TYPE
                        SYNTAX        Integer32
                        MAX-ACCESS    read-only
                        STATUS        deprecated
                        DESCRIPTION
                           "The number of external humidity sensors (regardless of
                             their current state) present on this pdu.
                             This is deprecated in favor of externalSensors"
                        ::= { environmental 3 }

-- the humidity sensors table

-- The humiditySensorTable table contains information on the pdu's external humidity sensors.

humiditySensorTable     OBJECT-TYPE
                        SYNTAX        SEQUENCE OF HumiditySensorEntryStruct
                        MAX-ACCESS    not-accessible
                        STATUS        deprecated
                        DESCRIPTION
                            "A list of humidity sensor entries. The number of
                             entries is given by the value of humiditySensorCount.
                             This is deprecated in favor of externalSensors"
                        ::= { environmental 4 }

humiditySensorEntry     OBJECT-TYPE
                        SYNTAX        HumiditySensorEntryStruct
                        MAX-ACCESS    not-accessible
                        STATUS        deprecated
                        DESCRIPTION
                            "An entry containing sensor reading and threshold
                            settings for a particular humidity sensor.
                             This is deprecated in favor of externalSensors"
                        INDEX         { humiditySensorIndex }
                        ::= { humiditySensorTable 1 }

HumiditySensorEntryStruct ::= SEQUENCE { humiditySensorIndex            Integer32,
                                 humiditySensorLabel                    DisplayString,
                                 humidity                               RelativeHumidity,
                                 humidityLowerWarning                   RelativeHumidity,
                                 humidityUpperWarning                   RelativeHumidity,
                                 humidityLowerCritical                  RelativeHumidity,
                                 humidityUpperCritical                  RelativeHumidity,
                                 humidityXCoordinate                    DisplayString,
                                 humidityYCoordinate                    DisplayString,
                                 humidityZCoordinate                    DisplayString }

humiditySensorIndex                OBJECT-TYPE
                                   SYNTAX        Integer32(1..256)
                                   MAX-ACCESS    not-accessible
                                   STATUS        deprecated
                                   DESCRIPTION
                                       "A unique value for each humidity sensor. Its value
                                        ranges between 1 and humiditySensorCount.
                                        This is deprecated in favor of externalSensors"
                                   ::= { humiditySensorEntry 1 }

humiditySensorLabel                OBJECT-TYPE
                                   SYNTAX        DisplayString
                                   MAX-ACCESS    read-write
                                   STATUS        deprecated
                                   DESCRIPTION
                                       "A settable human-readable label for the external humidity
                                       sensor.  One possible use for this label is to convey sensor
                                       location.
                                       This is deprecated in favor of externalSensors"
                                   ::= { humiditySensorEntry 2 }

humidity                           OBJECT-TYPE
                                   SYNTAX        RelativeHumidity
                                   MAX-ACCESS    read-only
                                   STATUS        deprecated
                                   DESCRIPTION
                                       "The value of the external humidity sensor reported
                                       as relative humidity (a percentage).
                                        This is deprecated in favor of externalSensors"
                                   ::= { humiditySensorEntry 3 }

humidityLowerWarning      OBJECT-TYPE
                                   SYNTAX        RelativeHumidity
                                   MAX-ACCESS    read-write
                                   STATUS        deprecated
                                   DESCRIPTION
                                       "The value of the lower warning (non-critical) threshold.
                                         This is deprecated in favor of externalSensors"
                                   ::= { humiditySensorEntry 4 }

humidityUpperWarning      OBJECT-TYPE
                                   SYNTAX        RelativeHumidity
                                   MAX-ACCESS    read-write
                                   STATUS        deprecated
                                   DESCRIPTION
                                       "The value of the upper warning (non-critical) threshold.
                                        This is deprecated in favor of externalSensors"
                                   ::= { humiditySensorEntry 5 }

humidityLowerCritical         OBJECT-TYPE
                                   SYNTAX        RelativeHumidity
                                   MAX-ACCESS    read-write
                                   STATUS        deprecated
                                   DESCRIPTION
                                       "The value of the lower critical threshold.
                                        This is deprecated in favor of externalSensors"
                                   ::= { humiditySensorEntry 6 }

humidityUpperCritical          OBJECT-TYPE
                                   SYNTAX        RelativeHumidity
                                   MAX-ACCESS    read-write
                                   STATUS        deprecated
                                   DESCRIPTION
                                       "The value of the upper critical threshold.
                                         This is deprecated in favor of externalSensors"
                                   ::= { humiditySensorEntry 7 }


humidityXCoordinate            OBJECT-TYPE
                                   SYNTAX        DisplayString
                                   MAX-ACCESS    read-write
                                   STATUS        deprecated
                                   DESCRIPTION
                                       "The value of X coordinate in freeform
                                         with  number of characters  <= 24
                                        This is deprecated in favor of externalSensors"
                                   ::= { humiditySensorEntry 8 }

humidityYCoordinate            OBJECT-TYPE
                                   SYNTAX        DisplayString
                                   MAX-ACCESS    read-write
                                   STATUS        deprecated
                                   DESCRIPTION
                                       "The value of Y coordinate in freeform
                                         with number of characters  <= 24
                                        This is deprecated in favor of externalSensors"
                                   ::= { humiditySensorEntry 9 }

humidityZCoordinate            OBJECT-TYPE
                                   SYNTAX        DisplayString
                                   MAX-ACCESS    read-write
                                   STATUS        deprecated
                                   DESCRIPTION
                                       "The value of Z coordinate in one of two formats:
                                          either freeform with  number of characters  <= 24
                                         or in Z units so that 0 =< integer value  <= 60
                                         This is deprecated in favor of externalSensors"
                                   ::= { humiditySensorEntry 10 }

-- the externalSensor table

-- The externalSensor table contains information on the pdu's external Sensors

externalSensorCount                  OBJECT-TYPE
                                      SYNTAX        Integer32(0..255)
                                      MAX-ACCESS    read-only
                                      STATUS        current
                                      DESCRIPTION
                                          "The number of external sensors"
                                      ::= { externalSensors 1}

reorderexternalSensorTableEntries    OBJECT-TYPE
                                      SYNTAX        DisplayString
                                      MAX-ACCESS    read-write
                                      STATUS        current
                                      DESCRIPTION
                                          "This is an operation. It has write-only semantics.
                                           GET operation will return the empty string.
                                           For SET operations, it specifies the new order of the externalSensorTable entries.

                                           a) The list must contain entries for each managed sensor, even if the sensor is not being moved.
                                           b) The list must not have more than 16 entries.
                                           c) 1 <= Valid sensorID <= 16
                                           d) The length of the list is the value of the largest sensorID in the
                                                original (before the move) list of managed sensors.
                                           e) Each sensorID must appear only once in the list.
                                           f) If there are missing numbers in the original list of sensorIDs,
                                                then each missing number must be indicated by a comma.


                                           EXAMPLE 1: Managed sensors have IDs 1,2,3,4,5
                                              Move 1 to 13; 2 to 8; 3 to 9; 4 is not moved; 5 moves to 2
                                              Existing Position     New Position
                                               1                -->     13
                                               2                -->     8
                                               3                -->     9
                                               4                -->     4
                                               5                -->     2
                                              Since the largest sensorID before the move is 5, the length of the list is 5
                                              Comma separated list is 13,8,9,4,2

                                           EXAMPLE 2: Managed sensors have IDs 2,5,6,7,11
                                             Sensor IDs 1,3,4,8,9,10 do not appear in the list.
                                             These positions must be indicated by commas.
                                             Move 2 to 13; 5 to 8; 6 to 9; 7 to 16; 11 does not move
                                              Existing Position     New Position
                                               2                -->     13
                                               5                -->     8
                                               6                -->     9
                                               7                -->     16
                                               11               -->    11
                                             Since the  largest sensorID before the move is 11, the length of the list is 11
                                             Comma separated list is    ,13,,,8,9,16,,,,11

                                            "
                                      ::= { externalSensors 2 }

externalSensorTable     OBJECT-TYPE
                SYNTAX        SEQUENCE OF ExternalSensorEntryStruct
                MAX-ACCESS    not-accessible
                STATUS        current
                DESCRIPTION
                    "A list of externalSensor  entries. The number of
                     entries is given by the value of externalSensorCount for the pdu."
                ::= { externalSensors 3 }

externalSensorEntry     OBJECT-TYPE
                SYNTAX        ExternalSensorEntryStruct
                MAX-ACCESS    not-accessible
                STATUS        current
                DESCRIPTION
                    "An externalSensor entry containing objects at the
                     for a particular PDU."
                INDEX         { sensorID }
                ::= { externalSensorTable 1 }

ExternalSensorEntryStruct ::= SEQUENCE {sensorID              Integer32,
                                    externalSensorType                      TypeOfSensorEnumeration,
                                    externalSensorSerialNumber              DisplayString,
                                    externalSensorName                      DisplayString,
                                    externalSensorChannelNumber             Integer32,
                                    externalSensorXCoordinate               DisplayString,
                                    externalSensorYCoordinate               DisplayString,
                                    externalSensorZCoordinate               DisplayString,
                                    externalBinarySensorSubtype             TypeOfSensorEnumeration,
                                    externalSensorUnits                     SensorUnitsEnumeration,
                                    externalSensorDecimalDigits             Unsigned32,
                                    externalSensorLowerCriticalThreshold    Integer32,
                                    externalSensorLowerWarningThreshold     Integer32,
                                    externalSensorUpperCriticalThreshold    Integer32,
                                    externalSensorUpperWarningThreshold     Integer32,
                                    externalSensorHysteresis                Unsigned32,
                                    externalSensorState                     StateOfSensorEnumeration,
                                    externalSensorValue                     Integer32                                                                                 }

sensorID                           OBJECT-TYPE
                                      SYNTAX        Integer32(1..256)
                                      MAX-ACCESS    not-accessible
                                      STATUS        current
                                      DESCRIPTION
                                          "A unique value for each sesnor. Its value
                                           ranges between 1 and the value of externalSensorCount."
                                      ::= { externalSensorEntry 1 }


externalSensorType                 OBJECT-TYPE
                                      SYNTAX        TypeOfSensorEnumeration
                                      MAX-ACCESS    read-only
                                      STATUS        current
                                      DESCRIPTION
                                          "The type of sensor"
                                      ::= { externalSensorEntry 2 }

externalSensorSerialNumber         OBJECT-TYPE
                                      SYNTAX        DisplayString
                                      MAX-ACCESS    read-only
                                      STATUS        current
                                      DESCRIPTION
                                          "The sensor serial number"
                                      ::= { externalSensorEntry 3 }

externalSensorName                 OBJECT-TYPE
                                      SYNTAX        DisplayString
                                      MAX-ACCESS    read-write
                                      STATUS        current
                                      DESCRIPTION
                                          "The user given name"
                                      ::= { externalSensorEntry 4 }


externalSensorChannelNumber    OBJECT-TYPE
                                      SYNTAX        Integer32
                                      MAX-ACCESS    read-only
                                      STATUS        current
                                      DESCRIPTION
                                          "The channel number, applies only to contact sensors;
                                           -1 for other sensors"
                                      ::= { externalSensorEntry 5 }

externalSensorXCoordinate          OBJECT-TYPE
                                      SYNTAX        DisplayString
                                      MAX-ACCESS    read-write
                                      STATUS        current
                                      DESCRIPTION
                                          "The X coordinate"
                                      ::= { externalSensorEntry 6 }

externalSensorYCoordinate          OBJECT-TYPE
                                      SYNTAX        DisplayString
                                      MAX-ACCESS    read-write
                                      STATUS        current
                                      DESCRIPTION
                                          "The Y coordinate"
                                      ::= { externalSensorEntry 7 }

externalSensorZCoordinate          OBJECT-TYPE
                                      SYNTAX        DisplayString
                                      MAX-ACCESS    read-write
                                      STATUS        current
                                      DESCRIPTION
                                          "The Z coordinate"
                                      ::= { externalSensorEntry 8 }

externalBinarySensorSubtype         OBJECT-TYPE
                                      SYNTAX        TypeOfSensorEnumeration
                                      MAX-ACCESS    read-only
                                      STATUS        current
                                      DESCRIPTION
                                          "The subtype of the binary sensor
                                           This OID is valid for discrete sensors only."
                                      ::= { externalSensorEntry 9 }

externalSensorUnits             OBJECT-TYPE
                                      SYNTAX        SensorUnitsEnumeration
                                      MAX-ACCESS    read-only
                                      STATUS        current
                                      DESCRIPTION
                                          "The base units. Does not apply (gets will return 0)
                                           to onOff, trip, vibration, waterDetection,
                                           smokeDetection sensors"
                                      ::= { externalSensorEntry 16 }

externalSensorDecimalDigits    OBJECT-TYPE
                                      SYNTAX        Unsigned32
                                      MAX-ACCESS    read-only
                                      STATUS        current
                                      DESCRIPTION
                                          "The number of digits displayed to the right of the decimal point.
                                           Does not apply (gets will return 0)
                                           to onOff, trip, vibration, waterDetection,
                                           smokeDetection sensors"
                                      ::= { externalSensorEntry 17 }

externalSensorLowerCriticalThreshold        OBJECT-TYPE
                                      SYNTAX        Integer32
                                      MAX-ACCESS    read-write
                                      STATUS        current
                                      DESCRIPTION
                                          "The lower critical threshold
                                           The value of this OID variable should be scaled by
                                           externalSensorDecimalDigits.  For example, if the value is 1 and
                                           externalSensorDecimalDigits is 2, then actual value is .01
                                           Does not apply (gets will return 0)
                                           to onOff, trip, vibration, waterDetection,
                                           smokeDetection sensors"
                                      ::= { externalSensorEntry 31 }

externalSensorLowerWarningThreshold      OBJECT-TYPE
                                      SYNTAX        Integer32
                                      MAX-ACCESS    read-write
                                      STATUS        current
                                      DESCRIPTION
                                          "The lower non-critical (warning) threshold
                                           The value of this OID variable should be scaled by
                                           externalSensorDecimalDigits.  For example, if the value is 1 and
                                           externalSensorDecimalDigits is 2, then actual value is .01
                                           Does not apply (gets will return 0)
                                           to onOff, trip, vibration, waterDetection,
                                           smokeDetection sensors"
                                      ::= { externalSensorEntry 32 }

externalSensorUpperCriticalThreshold        OBJECT-TYPE
                                      SYNTAX        Integer32
                                      MAX-ACCESS    read-write
                                      STATUS        current
                                      DESCRIPTION
                                          "The upper critical  threshold
                                           The value of this OID variable should be scaled by
                                           externalSensorDecimalDigits.  For example, if the value is 1 and
                                           externalSensorDecimalDigits is 2, then actual value is .01
                                           Does not apply (gets will return 0)
                                           to onOff, trip, vibration, waterDetection,
                                           smokeDetection sensors"
                                      ::= { externalSensorEntry 33 }

externalSensorUpperWarningThreshold         OBJECT-TYPE
                                      SYNTAX        Integer32
                                      MAX-ACCESS    read-write
                                      STATUS        current
                                      DESCRIPTION
                                          "The upper non-critical (warning) threshold
                                           The value of this OID variable should be scaled by
                                           externalSensorDecimalDigits.  For example, if the value is 1 and
                                           externalSensorDecimalDigits is 2, then actual value is .01
                                           Does not apply (gets will return 0)
                                           to onOff, trip, vibration, waterDetection,
                                           smokeDetection sensors"
                                      ::= { externalSensorEntry 34 }

externalSensorHysteresis        OBJECT-TYPE
                                      SYNTAX        Unsigned32
                                      MAX-ACCESS    read-write
                                      STATUS        current
                                      DESCRIPTION
                                          "The hysteresis used for deassertions
                                           The value of this OID variable should be scaled by
                                           externalSensorDecimalDigits.  For example, if the value is 1 and
                                           externalSensorDecimalDigits is 2, then actual value is 0.01.
                                           This parameter does not apply
                                           to onOff, trip, vibration, waterDetection,
                                           smokeDetection sensors."
                                      ::= { externalSensorEntry 35 }


externalSensorState                   OBJECT-TYPE
                                      SYNTAX        StateOfSensorEnumeration
                                      MAX-ACCESS    read-only
                                      STATUS        current
                                      DESCRIPTION
                                          "The sensor state"
                                      ::= { externalSensorEntry 40 }

externalSensorValue               OBJECT-TYPE
                                      SYNTAX        Integer32
                                      MAX-ACCESS    read-only
                                      STATUS        current
                                      DESCRIPTION
                                          "The sensor reading
                                           Does not apply (gets will return 0)
                                           to onOff, trip, vibration, waterDetection,
                                           smokeDetection sensors"
                                      ::= { externalSensorEntry 41 }

-- the line Current group

-- Implementation for line Inputs

lineCurrentCount     OBJECT-TYPE
                    SYNTAX        Integer32
                    MAX-ACCESS    read-only
                    STATUS        deprecated
                    DESCRIPTION
                       "The number of line currents (1 for single phase, 3 for 3 phase Delta-wired,
                         4 for 3 phase WYE wired).This object is deprecated in favour of inletPoleTable"
                    ::= { lineCurrents 1 }

-- the line input table

-- The lineCurrentTable table contains information on the line inputs.

lineCurrentTable     OBJECT-TYPE
                    SYNTAX        SEQUENCE OF LineCurrentEntryStruct
                    MAX-ACCESS    not-accessible
                    STATUS        deprecated
                    DESCRIPTION
                        "A list of line input entries. The number of
                         entries is given by the value of lineInputCount.
                         This object is deprecated in favour of inletPoleTable"
                    ::= { lineCurrents 2 }

lineCurrentEntry     OBJECT-TYPE
                    SYNTAX        LineCurrentEntryStruct
                    MAX-ACCESS    not-accessible
                    STATUS        deprecated
                    DESCRIPTION
                        "An entry containing  values and threshold
                        settings for a particular line input.This object is deprecated in favour of inletPoleTable"
                    INDEX         { lineCurrentIndex }
                    ::= { lineCurrentTable 1 }

LineCurrentEntryStruct ::= SEQUENCE { lineCurrentIndex                Integer32,
                                 lineCurrentLabel                    DisplayString,
                                 lineCurrent                           MilliAmps}

lineCurrentIndex                    OBJECT-TYPE
                                   SYNTAX        Integer32(1..256)
                                   MAX-ACCESS    not-accessible
                                   STATUS        deprecated
                                   DESCRIPTION
                                       "A unique value for each line input. Its value
                                        ranges between 1 and lineInputCount.
                                        This object is deprecated in favour of inletPoleTable"
                                   ::= { lineCurrentEntry 1 }

lineCurrentLabel                   OBJECT-TYPE
                                   SYNTAX      DisplayString
                                   MAX-ACCESS    read-only
                                   STATUS        deprecated
                                   DESCRIPTION
                                       "A string identifying the Line
                                          For Single Phase: L1
                                          For 3phase Delta wired outlets: L1, L2, L3
                                          For 3phase WYE Wired Outlets: L1, L2, L3, N
                                          This object is deprecated in favour of inletPoleTable"
                                   ::= { lineCurrentEntry 2 }

lineCurrent                          OBJECT-TYPE
                                   SYNTAX        MilliAmps
                                   MAX-ACCESS    read-only
                                   STATUS        deprecated
                                   DESCRIPTION
                                       "The value of the current reported in MilliAmps.
                                        This object is deprecated in favour of inletPoleTable"
                                   ::= { lineCurrentEntry 3 }

-- the circuitBreaker group

-- Implementation for circuit Breakers

circuitBreakerCount     OBJECT-TYPE
                    SYNTAX        Integer32
                    MAX-ACCESS    read-only
                    STATUS        current
                    DESCRIPTION
                       "The number of circuit breakers."
                    ::= { circuitBreaker 1 }
-- the circuit breaker table

-- The circuitBreakerTable table contains information on the circuit breakers.

circuitBreakerTable     OBJECT-TYPE
                    SYNTAX        SEQUENCE OF CircuitBreakerEntryStruct
                    MAX-ACCESS    not-accessible
                    STATUS        current
                    DESCRIPTION
                        "A list of line input entries. The number of
                         entries is given by the value of lineInputCount."
                    ::= { circuitBreaker 2 }

circuitBreakerEntry     OBJECT-TYPE
                    SYNTAX        CircuitBreakerEntryStruct
                    MAX-ACCESS    not-accessible
                    STATUS        current
                    DESCRIPTION
                        "An entry containing  values and threshold
                        settings for a particular line input."
                    INDEX         { circuitBreakerIndex }
                    ::= { circuitBreakerTable 1 }

CircuitBreakerEntryStruct ::= SEQUENCE { circuitBreakerIndex                     Integer32,
                                 circuitBreakerLabel                             DisplayString,
                                 circuitBreakerState                             INTEGER,
                                 circuitBreakerCurrentRating                     MilliAmps,
                                 circuitBreakerCurrent                           MilliAmps,
                                 circuitBreakerCurrentUpperWarning               MilliAmps,
                                 circuitBreakerCurrentUpperCritical              MilliAmps,
                                 circuitBreakerCurrentHysteresis                 Unsigned32 }

circuitBreakerIndex                    OBJECT-TYPE
                                   SYNTAX        Integer32(1..256)
                                   MAX-ACCESS    not-accessible
                                   STATUS        current
                                   DESCRIPTION
                                       "A unique value for each circuit breaker. Its value
                                        ranges between 1 and circuitBreakerCount."
                                   ::= { circuitBreakerEntry 1 }

circuitBreakerLabel                   OBJECT-TYPE
                                   SYNTAX        DisplayString
                                   MAX-ACCESS    read-only
                                   STATUS        current
                                   DESCRIPTION
                                       "A string identifying the circuit breaker  "
                                   ::= { circuitBreakerEntry 2 }

circuitBreakerState                   OBJECT-TYPE
                                   SYNTAX      INTEGER { ok(0),
                                                tripped(1) }
                                   MAX-ACCESS  read-only
                                   STATUS      current
                                   DESCRIPTION
                                          "The value for the  circuit breaker state ."
                                   ::= { circuitBreakerEntry 3 }

circuitBreakerCurrentRating        OBJECT-TYPE
                                   SYNTAX        MilliAmps
                                   MAX-ACCESS    read-only
                                   STATUS        current
                                   DESCRIPTION
                                       "The value of the circuit breaker current rating
                                       in MilliAmps."
                                   ::= { circuitBreakerEntry 4 }

circuitBreakerCurrent                          OBJECT-TYPE
                                   SYNTAX        MilliAmps
                                   MAX-ACCESS    read-only
                                   STATUS        current
                                   DESCRIPTION
                                       "The value of the current reported
                                       in MilliAmps."
                                   ::= { circuitBreakerEntry 5 }

circuitBreakerCurrentUpperWarning       OBJECT-TYPE
                                   SYNTAX        MilliAmps
                                   MAX-ACCESS    read-write
                                   STATUS        current
                                   DESCRIPTION
                                       "The value of the upper warning (non-critical) threshold."
                                   ::= { circuitBreakerEntry 7 }

circuitBreakerCurrentUpperCritical          OBJECT-TYPE
                                   SYNTAX        MilliAmps
                                   MAX-ACCESS    read-write
                                   STATUS        current
                                   DESCRIPTION
                                       "The value of the upper critical threshold."
                                   ::= { circuitBreakerEntry 9 }

circuitBreakerCurrentHysteresis        OBJECT-TYPE
                                      SYNTAX        Unsigned32
                                      MAX-ACCESS    read-write
                                      STATUS        current
                                      DESCRIPTION
                                          "The hysteresis used for deassertions
                                           reported in milliamps (1/1000th of an amp)"
                                      ::= { circuitBreakerEntry 10 }

-- the line Voltage group

-- Implementation for line Voltages

lineVoltageCount     OBJECT-TYPE
                    SYNTAX        Integer32
                    MAX-ACCESS    read-only
                    STATUS        deprecated
                    DESCRIPTION
                       "The number of line voltages (1 for single phase, 3 for 3 phase.
                        This object is deprecated in favour of inletPoleTable"
                    ::= { lineVoltages 1 }

-- the line voltage table

-- The linevoltageTable table contains information on the line voltages.

lineVoltageTable     OBJECT-TYPE
                    SYNTAX        SEQUENCE OF LineVoltageEntryStruct
                    MAX-ACCESS    not-accessible
                    STATUS        deprecated
                    DESCRIPTION
                        "A list of line input entries. The number of
                         entries is given by the value of lineInputCount.
                         This object is deprecated in favour of linletPoleTable"
                    ::= { lineVoltages 2 }

lineVoltageEntry     OBJECT-TYPE
                    SYNTAX        LineVoltageEntryStruct
                    MAX-ACCESS    not-accessible
                    STATUS        deprecated
                    DESCRIPTION
                        "An entry containing  values and threshold
                        settings for a particular line input.
                        This object is deprecated in favour of inletPoleTable"
                    INDEX         { lineVoltageIndex }
                    ::= { lineVoltageTable 1 }

LineVoltageEntryStruct ::= SEQUENCE { lineVoltageIndex                Integer32,
                                 lineVoltageLabel                    DisplayString,
                                 lineVoltage                           MilliVolts}

lineVoltageIndex                    OBJECT-TYPE
                                   SYNTAX        Integer32(1..256)
                                   MAX-ACCESS    not-accessible
                                   STATUS        deprecated
                                   DESCRIPTION
                                       "A unique value for each line input. Its value
                                        ranges between 1 and lineInputCount.
                                        This object is deprecated in favour of inletPoleTable"
                                   ::= { lineVoltageEntry 1 }

lineVoltageLabel                   OBJECT-TYPE
                                   SYNTAX      DisplayString
                                   MAX-ACCESS    read-only
                                   STATUS        deprecated
                                   DESCRIPTION
                                       "A string identifying the Line
                                          For Single Phase: L1
                                          For 3phase Delta-wired: L1-L2, L2-L3, L3-L1
                                          For 3phase Wye-wired: L1-N, L2-N, L3-N
                                          This object is deprecated in favour of inletPoleTable"
                                   ::= { lineVoltageEntry 2 }

lineVoltage                          OBJECT-TYPE
                                   SYNTAX        MilliVolts
                                   MAX-ACCESS    read-only
                                   STATUS        deprecated
                                   DESCRIPTION
                                       "The value of the voltage reported in MilliVolts.
                                        This object is deprecated in favour of inletPoleTable"
                                   ::= { lineVoltageEntry 3 }

-- the data Log group

-- Implementation for data Log

dataLogCount     OBJECT-TYPE
                    SYNTAX        Integer32
                    MAX-ACCESS    read-only
                    STATUS        current
                    DESCRIPTION
                       "The number of entries in the dataLog table which is a circular buffer."
                    ::= { dataLog 1 }

dataLogLatestIndex   OBJECT-TYPE
                       SYNTAX        Integer32(1..256)
                       MAX-ACCESS    read-only
                       STATUS        current
                       DESCRIPTION
                          "The index of the latest (most recent) entry in dataLogTable ."
                      ::= { dataLog 2 }

-- the data log

-- The dataLogTable  table contains the data log.

dataLogTable     OBJECT-TYPE
                    SYNTAX        SEQUENCE OF DataLogEntryStruct
                    MAX-ACCESS    not-accessible
                    STATUS        current
                    DESCRIPTION
                        "A list of data log entries. The number of
                         entries is given by the value of dataLogCount."
                    ::= { dataLog 3 }

dataLogEntry     OBJECT-TYPE
                    SYNTAX        DataLogEntryStruct
                    MAX-ACCESS    not-accessible
                    STATUS        current
                    DESCRIPTION
                        "An entry in the dataLog buffer containing  the unit data collected at the instant
                         specified by dataLogTimeStamp"
                    INDEX         { dataLogIndex  }
                    ::= { dataLogTable 1 }

DataLogEntryStruct ::= SEQUENCE { dataLogIndex                   Integer32,
                                  dataLogTimeStamp               Unsigned32,
                                  dataLogActivePower             Watts,
                                  dataLogApparentPower           VoltAmps,
                                  dataLogAvgActivePower          Watts,
                                  dataLogMaxActivePower          Watts,
                                  dataLogMinActivePower          Watts,
                                  dataLogAvgApparentPower        VoltAmps,
                                  dataLogMaxApparentPower        VoltAmps,
                                  dataLogMinApparentPower        VoltAmps}

dataLogIndex                    OBJECT-TYPE
                                   SYNTAX        Integer32(1..256)
                                   MAX-ACCESS    not-accessible
                                   STATUS        current
                                   DESCRIPTION
                                       "A unique value for each data sample. Its value
                                        ranges between 1 and dataLogCount ."
                                   ::= { dataLogEntry 1 }

dataLogTimeStamp                   OBJECT-TYPE
                                   SYNTAX      Unsigned32
                                   MAX-ACCESS    read-only
                                   STATUS        current
                                   DESCRIPTION
                                       "The time when the data was collected. It is measured in seconds relative to
                                        January 1, 1970 (midnight UTC/GMT), i.e a value of 0 indicates
                                        January 1, 1970 (midnight UTC/GMT)"
                                   ::= { dataLogEntry 2 }

dataLogActivePower         OBJECT-TYPE
                          SYNTAX      Watts
                          MAX-ACCESS  read-only
                          STATUS      deprecated
                          DESCRIPTION
                              "The value for the pdu's active power sensor in watts.
                               This has been deprecated in favor of
                                  dataLogAvgActivePower, dataLogMaxActivePower,dataLogMinActivePower "
                          ::= { dataLogEntry 3 }

dataLogApparentPower         OBJECT-TYPE
                          SYNTAX      VoltAmps
                          MAX-ACCESS  read-only
                          STATUS      deprecated
                          DESCRIPTION
                              "The value for the pdu's apparent power sensor in volt-amps.
                               This has been deprecated in favor of
                                  dataLogAvgApparentPower, dataLogMaxApparentPower,dataLogMinApparentPower "
                          ::= { dataLogEntry 4 }

dataLogAvgActivePower       OBJECT-TYPE
                          SYNTAX      Watts
                          MAX-ACCESS  read-only
                          STATUS      current
                          DESCRIPTION
                              "The average  active power for this measurement period"
                          ::= { dataLogEntry 5 }


dataLogMaxActivePower         OBJECT-TYPE
                          SYNTAX      Watts
                          MAX-ACCESS  read-only
                          STATUS      current
                          DESCRIPTION
                              "The maximum  active power for this measurement period"
                          ::= { dataLogEntry 6 }

dataLogMinActivePower         OBJECT-TYPE
                          SYNTAX      Watts
                          MAX-ACCESS  read-only
                          STATUS      current
                          DESCRIPTION
                              "The minimum  active power for this measurement period"
                          ::= { dataLogEntry 7 }

dataLogAvgApparentPower       OBJECT-TYPE
                          SYNTAX      VoltAmps
                          MAX-ACCESS  read-only
                          STATUS      current
                          DESCRIPTION
                              "The average  apparent power for this measurement period"
                          ::= { dataLogEntry 8 }

dataLogMaxApparentPower         OBJECT-TYPE
                          SYNTAX      VoltAmps
                          MAX-ACCESS  read-only
                          STATUS      current
                          DESCRIPTION
                              "The maximum  apparent power for this measurement period"
                          ::= { dataLogEntry 9 }

dataLogMinApparentPower         OBJECT-TYPE
                          SYNTAX      VoltAmps
                          MAX-ACCESS  read-only
                          STATUS      current
                          DESCRIPTION
                              "The minimum  apparent power for this measurement period"
                          ::= { dataLogEntry 10 }

-- the outlets data group

-- Implementation for storing outlet data

-- the outlets data table

-- The outlets read-only data table contains information on the pdu's outlets.
-- This data can be uploaded to the manager

dataLogOutletTable     OBJECT-TYPE
                SYNTAX        SEQUENCE OF DataLogOutletEntryStruct
                MAX-ACCESS    not-accessible
                STATUS        current
                DESCRIPTION
                    "A list of outlet entries. The number of
                     entries is given by the value of outletCount."
                ::= { dataLogOutlet 1 }

dataLogOutletEntry     OBJECT-TYPE
                SYNTAX        DataLogOutletEntryStruct
                MAX-ACCESS    not-accessible
                STATUS        current
                DESCRIPTION
                    "An entry in the data log containing outlet level data
                     for a particular outlet."
                INDEX         { dataLogIndex,dataLogOutletIndex }
                ::= { dataLogOutletTable  1 }

DataLogOutletEntryStruct ::= SEQUENCE { dataLogOutletIndex                        Integer32,
                                 dataLogOutletCurrent                      MilliAmps,
                                 dataLogOutletVoltage                      MilliVolts,
                                 dataLogOutletPowerFactor                  PowerFactorPercentage,
                                 dataLogOutletOnTime                       Unsigned32,
                                 dataLogOutletWattHours                    WattHours,
                                 dataLogAvgOutletCurrent                   MilliAmps,
                                 dataLogMaxOutletCurrent                   MilliAmps,
                                 dataLogMinOutletCurrent                   MilliAmps,
                                 dataLogAvgOutletVoltage                   MilliVolts,
                                 dataLogMaxOutletVoltage                   MilliVolts,
                                 dataLogMinOutletVoltage                   MilliVolts,
                                 dataLogAvgOutletPowerFactor               PowerFactorPercentage,
                                 dataLogMaxOutletPowerFactor               PowerFactorPercentage,
                                 dataLogMinOutletPowerFactor               PowerFactorPercentage,
                                 dataLogAvgOutletWattHours                 WattHours,
                                 dataLogMaxOutletWattHours                 WattHours,
                                 dataLogMinOutletWattHours                 WattHours
                                  }

dataLogOutletIndex                           OBJECT-TYPE
                                      SYNTAX        Integer32(1..256)
                                      MAX-ACCESS    not-accessible
                                      STATUS        current
                                      DESCRIPTION
                                          "A unique value for each outlet. Its value
                                           ranges between 1 and the value of outletCount."
                                      ::= { dataLogOutletEntry 1 }

dataLogOutletCurrent                         OBJECT-TYPE
                                      SYNTAX        MilliAmps
                                      MAX-ACCESS    read-only
                                      STATUS        deprecated
                                      DESCRIPTION
                                          "A unique value for the current sensor
                                           attached to the outlet.  This value is
                                           reported in milliamps (1/1000th of an amp)
                                           This has been deprecated in favor of
                                              dataLogAvgOutletCurrent , dataLogMaxOutletCurrent ,dataLogMinOutletCurrent  "
                                      ::= { dataLogOutletEntry 2 }

dataLogOutletVoltage                         OBJECT-TYPE
                                      SYNTAX        MilliVolts
                                      MAX-ACCESS    read-only
                                      STATUS        deprecated
                                      DESCRIPTION
                                          "A unique value for the voltage sensor
                                           attached to the outlet.This value is
                                           reported in millivolts (1/1000th of a volt)
                                           This has been deprecated in favor of
                                              dataLogAvgOutletVoltage , dataLogMaxOutletVoltage ,dataLogMinOutletVoltage "
                                      ::= { dataLogOutletEntry 3 }

dataLogOutletPowerFactor                     OBJECT-TYPE
                                      SYNTAX        PowerFactorPercentage
                                      MAX-ACCESS    read-only
                                      STATUS        deprecated
                                      DESCRIPTION
                                          "A unique value for the power factor
                                           of the outlet. The reading represents a
                                           percentage in the range of 0% to 100%.
                                           This has been deprecated in favor of
                                              dataLogAvgOutletPowerFactor, dataLogMaxOutletPowerFactor,dataLogMinOutletPowerFactor "
                                      ::= { dataLogOutletEntry 4 }

dataLogOutletOnTime                              OBJECT-TYPE
                                      SYNTAX        Unsigned32
                                      MAX-ACCESS    read-only
                                      STATUS        current
                                      DESCRIPTION
                                          "The amount of time since this outlet was last switched on.
                                            This value is reported in  seconds. "
                                      ::= { dataLogOutletEntry 5 }

dataLogOutletWattHours                         OBJECT-TYPE
                                      SYNTAX        WattHours
                                      MAX-ACCESS    read-only
                                      STATUS        deprecated
                                      DESCRIPTION
                                          "The cumulative Active Energy for this outlet. This value is
                                           reported in WattHours
                                           This has been deprecated in favor of
                                              dataLogAvgOutletWattHours , dataLogMaxOutletWattHours ,dataLogMinOutletWattHours"
                                      ::= { dataLogOutletEntry 6 }

dataLogAvgOutletCurrent                         OBJECT-TYPE
                                      SYNTAX        MilliAmps
                                      MAX-ACCESS    read-only
                                      STATUS        current
                                      DESCRIPTION
                                          "The Average value for the measurement period:
                                            A unique value for the current sensor
                                           attached to the outlet.  This value is
                                           reported in milliamps (1/1000th of an amp)"
                                      ::= { dataLogOutletEntry 7 }

dataLogMaxOutletCurrent                         OBJECT-TYPE
                                      SYNTAX        MilliAmps
                                      MAX-ACCESS    read-only
                                      STATUS        current
                                      DESCRIPTION
                                          "The Maximum value for the measurement period:
                                           A unique value for the current sensor
                                           attached to the outlet.  This value is
                                           reported in milliamps (1/1000th of an amp)"
                                      ::= { dataLogOutletEntry 8 }

dataLogMinOutletCurrent                         OBJECT-TYPE
                                      SYNTAX        MilliAmps
                                      MAX-ACCESS    read-only
                                      STATUS        current
                                      DESCRIPTION
                                          "The Minimum value for the measurement period:
                                            A unique value for the current sensor
                                           attached to the outlet.  This value is
                                           reported in milliamps (1/1000th of an amp)"
                                      ::= { dataLogOutletEntry 9 }

dataLogAvgOutletVoltage                         OBJECT-TYPE
                                      SYNTAX        MilliVolts
                                      MAX-ACCESS    read-only
                                      STATUS        current
                                      DESCRIPTION
                                          "The Average value for the measurement period:
                                           A unique value for the voltage sensor
                                           attached to the outlet.This value is
                                           reported in millivolts (1/1000th of a volt)"
                                      ::= { dataLogOutletEntry 10 }

dataLogMaxOutletVoltage                         OBJECT-TYPE
                                      SYNTAX        MilliVolts
                                      MAX-ACCESS    read-only
                                      STATUS        current
                                      DESCRIPTION
                                          "The Maximum value for the measurement period:
                                           A unique value for the voltage sensor
                                           attached to the outlet.This value is
                                           reported in millivolts (1/1000th of a volt)"
                                      ::= { dataLogOutletEntry 11 }

dataLogMinOutletVoltage                         OBJECT-TYPE
                                      SYNTAX        MilliVolts
                                      MAX-ACCESS    read-only
                                      STATUS        current
                                      DESCRIPTION
                                          "The Minimum value for the measurement period:
                                            A unique value for the voltage sensor
                                           attached to the outlet.This value is
                                           reported in millivolts (1/1000th of a volt)"
                                      ::= { dataLogOutletEntry 12 }


dataLogAvgOutletPowerFactor                         OBJECT-TYPE
                                      SYNTAX       PowerFactorPercentage
                                      MAX-ACCESS    read-only
                                      STATUS        current
                                      DESCRIPTION
                                          "The Average value for the measurement period:
                                           A unique value for the power factor
                                           of the outlet. The reading represents a
                                           percentage in the range of 0% to 100%"
                                      ::= { dataLogOutletEntry 13 }

dataLogMaxOutletPowerFactor                         OBJECT-TYPE
                                      SYNTAX        PowerFactorPercentage
                                      MAX-ACCESS    read-only
                                      STATUS        current
                                      DESCRIPTION
                                          "The Maximum value for the measurement period:
                                           A unique value for the power factor
                                           of the outlet. The reading represents a
                                           percentage in the range of 0% to 100%"
                                      ::= { dataLogOutletEntry 14 }

dataLogMinOutletPowerFactor                         OBJECT-TYPE
                                      SYNTAX        PowerFactorPercentage
                                      MAX-ACCESS    read-only
                                      STATUS        current
                                      DESCRIPTION
                                          "The Minimum value for the measurement period:
                                           A unique value for the power factor
                                           of the outlet. The reading represents a
                                           percentage in the range of 0% to 100%"
                                      ::= { dataLogOutletEntry 15 }

dataLogAvgOutletWattHours                         OBJECT-TYPE
                                      SYNTAX        WattHours
                                      MAX-ACCESS    read-only
                                      STATUS        current
                                      DESCRIPTION
                                          "The Average value for the measurement period:
                                            The cumulative Active Energy for this outlet. This value is
                                           reported in WattHours"
                                      ::= { dataLogOutletEntry 16 }

dataLogMaxOutletWattHours                         OBJECT-TYPE
                                      SYNTAX        WattHours
                                      MAX-ACCESS    read-only
                                      STATUS        current
                                      DESCRIPTION
                                          "The Maximum value for the measurement period:
                                             The cumulative Active Energy for this outlet. This value is
                                           reported in WattHours"
                                      ::= { dataLogOutletEntry 17 }

dataLogMinOutletWattHours                         OBJECT-TYPE
                                      SYNTAX        WattHours
                                      MAX-ACCESS    read-only
                                      STATUS        current
                                      DESCRIPTION
                                          "The Minimum value for the measurement period:
                                             The cumulative Active Energy for this outlet. This value is
                                           reported in WattHours"
                                      ::= { dataLogOutletEntry 18 }



-- the circuitBreaker Data group

-- Implementation for circuit Breakers

-- the circuit breaker table

-- The circuitBreakerTable table contains information on the circuit breakers.

dataLogCircuitBreakerTable     OBJECT-TYPE
                    SYNTAX        SEQUENCE OF DataLogCircuitBreakerEntryStruct
                    MAX-ACCESS    not-accessible
                    STATUS        current
                    DESCRIPTION
                        "A list of circuit breaker entries. The number of
                         entries is given by the value of circuitBreakerCount."
                    ::= { dataLogCircuitBreaker 1 }

dataLogCircuitBreakerEntry     OBJECT-TYPE
                    SYNTAX        DataLogCircuitBreakerEntryStruct
                    MAX-ACCESS    not-accessible
                    STATUS        current
                    DESCRIPTION
                        "An entry in the data log containing circuit breaker values"
                    INDEX         { dataLogIndex, dataLogCircuitBreakerIndex }
                    ::= { dataLogCircuitBreakerTable 1 }

DataLogCircuitBreakerEntryStruct ::= SEQUENCE { dataLogCircuitBreakerIndex                     Integer32,
                                                dataLogCircuitBreakerCurrent                   MilliAmps,
                                                dataLogAvgCircuitBreakerCurrent                MilliAmps,
                                                dataLogMaxCircuitBreakerCurrent                MilliAmps,
                                                dataLogMinCircuitBreakerCurrent                MilliAmps  }

dataLogCircuitBreakerIndex                    OBJECT-TYPE
                                   SYNTAX        Integer32(1..256)
                                   MAX-ACCESS    not-accessible
                                   STATUS        current
                                   DESCRIPTION
                                       "A unique value for each circuit breaker. Its value
                                        ranges between 1 and circuitBreakerCount."
                                   ::= { dataLogCircuitBreakerEntry 1 }

dataLogCircuitBreakerCurrent                          OBJECT-TYPE
                                   SYNTAX        MilliAmps
                                   MAX-ACCESS    read-only
                                   STATUS        deprecated
                                   DESCRIPTION
                                       "The value of the current reported
                                       in MilliAmps.
                                        This has been deprecated in favor of
                                              dataLogAvgCircuitBreakerCurrent, dataLogMaxOutletCircuitBreakerCurrent,
                                              dataLogMinCircuitBreakerCurrent "
                                   ::= { dataLogCircuitBreakerEntry 2 }

dataLogAvgCircuitBreakerCurrent                      OBJECT-TYPE
                                   SYNTAX        MilliAmps
                                   MAX-ACCESS    read-only
                                   STATUS        current
                                   DESCRIPTION
                                       "The Average value for the measurement period:
                                        The value of the current reported
                                       in MilliAmps."
                                   ::= { dataLogCircuitBreakerEntry 3 }

dataLogMaxCircuitBreakerCurrent                      OBJECT-TYPE
                                   SYNTAX        MilliAmps
                                   MAX-ACCESS    read-only
                                   STATUS        current
                                   DESCRIPTION
                                       "The Maximum value for the measurement period:
                                        The value of the current reported
                                       in MilliAmps."
                                   ::= { dataLogCircuitBreakerEntry 4 }

dataLogMinCircuitBreakerCurrent                      OBJECT-TYPE
                                   SYNTAX        MilliAmps
                                   MAX-ACCESS    read-only
                                   STATUS        current
                                   DESCRIPTION
                                       "The Minimum value for the measurement period:
                                         The value of the current reported
                                       in MilliAmps."
                                   ::= { dataLogCircuitBreakerEntry 5 }


-- the Input Line group

-- Implementation for Input Line

-- the line input table

-- The dataLogInputLineTable table contains information on the line inputs.

dataLogInputLineTable     OBJECT-TYPE
                    SYNTAX        SEQUENCE OF DataLogInputLineEntryStruct
                    MAX-ACCESS    not-accessible
                    STATUS        deprecated
                    DESCRIPTION
                        "A list of line input entries. The number of
                         entries is given by the value of lineCurrentCount.
                         This object is deprecated in favour of dataLogInletLineTable"
                    ::= { dataLogInputLine 1 }

dataLogInputLineEntry     OBJECT-TYPE
                    SYNTAX        DataLogInputLineEntryStruct
                    MAX-ACCESS    not-accessible
                    STATUS        deprecated
                    DESCRIPTION
                        "An entry in the data log containing  input line values for a particular input line.
                        This object is deprecated in favour of dataLogInletLineTable"
                    INDEX         { dataLogIndex,dataLogInputLineIndex }
                    ::= { dataLogInputLineTable 1 }

DataLogInputLineEntryStruct ::= SEQUENCE { dataLogInputLineIndex                Integer32,
                                          dataLogInputLineCurrent               MilliAmps,
                                          dataLogInputLineVoltage               MilliVolts}

dataLogInputLineIndex                    OBJECT-TYPE
                                   SYNTAX        Integer32(1..256)
                                   MAX-ACCESS    not-accessible
                                   STATUS        deprecated
                                   DESCRIPTION
                                       "A unique value for each line input. Its value
                                        ranges between 1 and inletTable(inletIndex).inletPoleCount.
                                        This object is deprecated in favour of dataLogInletLineTable"
                                   ::= { dataLogInputLineEntry 1 }

dataLogInputLineCurrent                          OBJECT-TYPE
                                   SYNTAX        MilliAmps
                                   MAX-ACCESS    read-only
                                   STATUS        deprecated
                                   DESCRIPTION
                                       "The value of the current reported
                                       in MilliAmps.
                                          For Single Phase: Input Line Current
                                          For 3phase Delta-wired: Current for L1, L2, L3
                                          For 3phase WYE-wired: Current for L1, L2, L3, N
                                          This object is deprecated in favour of dataLogInletLineTable"
                                   ::= { dataLogInputLineEntry 2 }

dataLogInputLineVoltage                          OBJECT-TYPE
                                   SYNTAX        MilliVolts
                                   MAX-ACCESS    read-only
                                   STATUS        deprecated
                                   DESCRIPTION
                                       "The value of the voltage reported
                                       in MilliVolts.
                                          For Single Phase: Input Line Voltage
                                          For 3phase Delta-wired: Voltages for L1-L2, L2-L3, L3-L1
                                          For 3phase WYE-wired: Voltages for L1-N, L2-N, L3-N
                                          This object is deprecated in favour of dataLogInletLineTable"
                                   ::= { dataLogInputLineEntry 3 }

-- the data Log inlets group

-- the inlets table for dataLog

dataLogInletTable     OBJECT-TYPE
                SYNTAX        SEQUENCE OF DataLogInletEntryStruct
                MAX-ACCESS    not-accessible
                STATUS        current
                DESCRIPTION
                    "A list of inlet entries. The number of
                     entries is given by the value of inletCount."
                ::= { dataLogInlet 2 }

dataLogInletEntry     OBJECT-TYPE
                SYNTAX        DataLogInletEntryStruct
                MAX-ACCESS    not-accessible
                STATUS        current
                DESCRIPTION
                    "An inlet entry containing objects at the
                     for a particular outlet."
                INDEX         { dataLogIndex, dataLogInletIndex }
                ::= { dataLogInletTable 1 }

DataLogInletEntryStruct ::= SEQUENCE { dataLogInletIndex                      Integer32,
                                       dataLogInletCurrentUnbalance           DisplayString,
                                       dataLogInletActivePower                Watts,
                                       dataLogInletApparentPower              VoltAmps,
                                       dataLogInletActiveEnergy               WattHours,
                                       dataLogAvgInletCurrentUnbalance        DisplayString,
                                       dataLogMaxInletCurrentUnbalance        DisplayString,
                                       dataLogMinInletCurrentUnbalance        DisplayString,
                                       dataLogAvgInletActivePower             Watts,
                                       dataLogMaxInletActivePower             Watts,
                                       dataLogMinInletActivePower             Watts,
                                       dataLogAvgInletApparentPower           VoltAmps,
                                       dataLogMaxInletApparentPower           VoltAmps,
                                       dataLogMinInletApparentPower           VoltAmps,
                                       dataLogAvgInletActiveEnergy            WattHours,
                                       dataLogMaxInletActiveEnergy            WattHours,
                                       dataLogMinInletActiveEnergy            WattHours
                              }

dataLogInletIndex                           OBJECT-TYPE
                                      SYNTAX        Integer32(1..256)
                                      MAX-ACCESS    not-accessible
                                      STATUS        current
                                      DESCRIPTION
                                          "A unique value for each inlet. Its value
                                           ranges between 1 and the value of inletCount."
                                      ::= { dataLogInletEntry 1 }

dataLogInletCurrentUnbalance             OBJECT-TYPE
                                      SYNTAX        DisplayString
                                      MAX-ACCESS    read-only
                                      STATUS        deprecated
                                      DESCRIPTION
                                         "A string displaying the current unbalance in percent.
                                           It will have the value NA if the feature is disabled,
                                           the PX is not a 3-phase unit,or the average of the line currents is zero
                                           This has been deprecated in favor of
                                              dataLogAvgInletCurrentUnbalance, dataLogMaxInletCurrentUnbalance,
                                              dataLogMinInletCurrentUnbalance "
                                      ::= { dataLogInletEntry 10 }

dataLogInletActivePower                     OBJECT-TYPE
                                      SYNTAX        Watts
                                      MAX-ACCESS    read-only
                                      STATUS        deprecated
                                      DESCRIPTION
                                          "The active power for the inlet
                                           This value is reported in Watts.
                                           This has been deprecated in favor of
                                              dataLogAvgInletActivePower, dataLogMaxInletActivePower,
                                              dataLogMinInletActivePower"
                                      ::= { dataLogInletEntry 11 }

dataLogInletApparentPower                   OBJECT-TYPE
                                      SYNTAX        VoltAmps
                                      MAX-ACCESS    read-only
                                      STATUS        deprecated
                                      DESCRIPTION
                                          "The apparent power for the inlet.
                                           This value is reported in Volt-Amps
                                           This has been deprecated in favor of
                                              dataLogAvgInletApparentPower, dataLogMaxInletApparentPower,
                                              dataLogMinInletApparentPower"
                                      ::= { dataLogInletEntry 12 }

dataLogInletActiveEnergy                         OBJECT-TYPE
                                      SYNTAX        WattHours
                                      MAX-ACCESS    read-only
                                      STATUS        deprecated
                                      DESCRIPTION
                                          "The value of the cumulative active energy for this inlet.
                                           This value is reported in WattHours
                                           This has been deprecated in favor of
                                              dataLogAvgInletActiveEnergy, dataLogMaxInletActiveEnergy,
                                              dataLogMinInletActiveEnergy"
                                      ::= { dataLogInletEntry 13 }

dataLogAvgInletCurrentUnbalance             OBJECT-TYPE
                                      SYNTAX        DisplayString
                                      MAX-ACCESS    read-only
                                      STATUS        current
                                      DESCRIPTION
                                         "The average value of the current unbalance for this measurement period
                                           A string displaying the current unbalance in percent.
                                           It will have the value NA if the feature is disabled,
                                           the PX is not a 3-phase unit,or the average of the line currents is zero"
                                      ::= { dataLogInletEntry 14 }

dataLogMaxInletCurrentUnbalance             OBJECT-TYPE
                                      SYNTAX        DisplayString
                                      MAX-ACCESS    read-only
                                      STATUS        current
                                      DESCRIPTION
                                         "The Maximum value for the measurement period:
                                           A string displaying the current unbalance in percent.
                                           It will have the value NA if the feature is disabled,
                                           the PX is not a 3-phase unit,or the average of the line currents is zero"
                                      ::= { dataLogInletEntry 15 }

dataLogMinInletCurrentUnbalance             OBJECT-TYPE
                                      SYNTAX        DisplayString
                                      MAX-ACCESS    read-only
                                      STATUS        current
                                      DESCRIPTION
                                         "The Minimum value for the measurement period:
                                           A string displaying the current unbalance in percent.
                                           It will have the value NA if the feature is disabled,
                                           the PX is not a 3-phase unit,or the average of the line currents is zero"
                                      ::= { dataLogInletEntry 16 }

dataLogAvgInletActivePower             OBJECT-TYPE
                                      SYNTAX        Watts
                                      MAX-ACCESS    read-only
                                      STATUS        current
                                      DESCRIPTION
                                         "The Average value for the measurement period:
                                          The active power for the inlet
                                           This value is reported in Watts."
                                      ::= { dataLogInletEntry 17 }

dataLogMaxInletActivePower             OBJECT-TYPE
                                      SYNTAX        Watts
                                      MAX-ACCESS    read-only
                                      STATUS        current
                                      DESCRIPTION
                                         "The Maximum value for the measurement period:
                                           The active power for the inlet
                                           This value is reported in Watts."
                                      ::= { dataLogInletEntry 18 }

dataLogMinInletActivePower             OBJECT-TYPE
                                      SYNTAX        Watts
                                      MAX-ACCESS    read-only
                                      STATUS        current
                                      DESCRIPTION
                                         "The Minimum value for the measurement period:
                                           The active power for the inlet
                                           This value is reported in Watts."
                                      ::= { dataLogInletEntry 19 }

dataLogAvgInletApparentPower             OBJECT-TYPE
                                      SYNTAX        VoltAmps
                                      MAX-ACCESS    read-only
                                      STATUS        current
                                      DESCRIPTION
                                         "The Average value for the measurement period:
                                          The apparent power for the inlet.
                                           This value is reported in Volt-Amps"
                                      ::= { dataLogInletEntry 20 }

dataLogMaxInletApparentPower             OBJECT-TYPE
                                      SYNTAX        VoltAmps
                                      MAX-ACCESS    read-only
                                      STATUS        current
                                      DESCRIPTION
                                         "The Maximum value for the measurement period:
                                           The apparent power for the inlet.
                                           This value is reported in Volt-Amps"
                                      ::= { dataLogInletEntry 21 }

dataLogMinInletApparentPower             OBJECT-TYPE
                                      SYNTAX        VoltAmps
                                      MAX-ACCESS    read-only
                                      STATUS        current
                                      DESCRIPTION
                                         "The Minimum value for the measurement period:
                                           The apparent power for the inlet.
                                           This value is reported in Volt-Amps"
                                      ::= { dataLogInletEntry 22 }

dataLogAvgInletActiveEnergy              OBJECT-TYPE
                                      SYNTAX        WattHours
                                      MAX-ACCESS    read-only
                                      STATUS        current
                                      DESCRIPTION
                                         " The Average value for the measurement period:
                                           The value of the cumulative active energy for this inlet.
                                           This value is reported in WattHours"
                                      ::= { dataLogInletEntry 23 }

dataLogMaxInletActiveEnergy              OBJECT-TYPE
                                      SYNTAX        WattHours
                                      MAX-ACCESS    read-only
                                      STATUS        current
                                      DESCRIPTION
                                         "The Maximum value for the measurement period:
                                           The value of the cumulative active energy for this inlet.
                                           This value is reported in WattHours"
                                      ::= { dataLogInletEntry 24 }

dataLogMinInletActiveEnergy              OBJECT-TYPE
                                      SYNTAX        WattHours
                                      MAX-ACCESS    read-only
                                      STATUS        current
                                      DESCRIPTION
                                         "The Minimum value for the measurement period:
                                           The value of the cumulative active energy for this inlet.
                                           This value is reported in WattHours"
                                      ::= { dataLogInletEntry 25 }




-- the dataLogInletPoleTable

-- The dataLogInletPoleTable table contains information on the inlet poles.

dataLogInletPoleTable     OBJECT-TYPE
                    SYNTAX        SEQUENCE OF DataLogInletPoleEntryStruct
                    MAX-ACCESS    not-accessible
                    STATUS        current
                    DESCRIPTION
                        "A list of line input entries. The number of
                         entries is given by the value of dataLoginletTable(dataLogInletIndex).inletPoleCount."
                    ::= { dataLogInletPole 1 }

dataLogInletPoleEntry     OBJECT-TYPE
                    SYNTAX        DataLogInletPoleEntryStruct
                    MAX-ACCESS    not-accessible
                    STATUS        current
                    DESCRIPTION
                        "An entry in the data log containing  input line values
                        for a particular input line."
                    INDEX         { dataLogIndex, dataLogInletIndex, dataLogInletPoleIndex }
                    ::= { dataLogInletPoleTable 1 }

DataLogInletPoleEntryStruct ::= SEQUENCE { dataLogInletPoleIndex                Integer32,
                                          dataLogInletPoleCurrent               MilliAmps,
                                          dataLogInletPoleVoltage               MilliVolts,
                                          dataLogAvgInletPoleCurrent            MilliAmps,
                                          dataLogMaxInletPoleCurrent            MilliAmps,
                                          dataLogMinInletPoleCurrent            MilliAmps,
                                          dataLogAvgInletPoleVoltage            MilliVolts,
                                          dataLogMaxInletPoleVoltage            MilliVolts,
                                          dataLogMinInletPoleVoltage            MilliVolts,
                                          dataLogAvgInletPoleActivePower        Watts,
                                          dataLogMaxInletPoleActivePower        Watts,
                                          dataLogMinInletPoleActivePower        Watts,
                                          dataLogAvgInletPoleApparentPower      VoltAmps,
                                          dataLogMaxInletPoleApparentPower      VoltAmps,
                                          dataLogMinInletPoleApparentPower      VoltAmps,
                                          dataLogAvgInletPoleActiveEnergy       WattHours,
                                          dataLogMaxInletPoleActiveEnergy       WattHours,
                                          dataLogMinInletPoleActiveEnergy       WattHours}

dataLogInletPoleIndex                    OBJECT-TYPE
                                   SYNTAX        Integer32(1..256)
                                   MAX-ACCESS    not-accessible
                                   STATUS        current
                                   DESCRIPTION
                                       "A unique value for each line input. Its value
                                        ranges between 1 and lineCurrentCount."
                                   ::= { dataLogInletPoleEntry 1 }

dataLogInletPoleCurrent                          OBJECT-TYPE
                                   SYNTAX        MilliAmps
                                   MAX-ACCESS    read-only
                                   STATUS        deprecated
                                   DESCRIPTION
                                       "The value of the current reported
                                       in MilliAmps.
                                          For Single Phase: Input Line Current
                                          For 3phase Delta-wired: Current for L1, L2, L3
                                          For 3phase WYE-wired: Current for L1, L2, L3, N
                                          This has been deprecated in favor of
                                              dataLogAvgInletPoleCurrent, dataLogMaxInletPoleCurrent,
                                              dataLogMinInletPoleCurrent"
                                   ::= { dataLogInletPoleEntry 2 }

dataLogInletPoleVoltage                          OBJECT-TYPE
                                   SYNTAX        MilliVolts
                                   MAX-ACCESS    read-only
                                   STATUS        deprecated
                                   DESCRIPTION
                                       "The value of the voltage reported
                                       in MilliVolts.
                                          For Single Phase: Input Line Voltage
                                          For 3phase Delta-wired: Voltages for L1-L2, L2-L3, L3-L1
                                          For 3phase WYE-wired: Voltages for L1-N, L2-N, L3-N
                                          This has been deprecated in favor of
                                              dataLogAvgInletPoleVoltage, dataLogMaxInletPoleVoltage,
                                              dataLogMinInletPoleVoltage"
                                   ::= { dataLogInletPoleEntry 3 }

dataLogAvgInletPoleCurrent                          OBJECT-TYPE
                                   SYNTAX        MilliAmps
                                   MAX-ACCESS    read-only
                                   STATUS        current
                                   DESCRIPTION
                                       "The Average value for the measurement period:
                                        The value of the current reported
                                       in MilliAmps.
                                          For Single Phase: Input Line Current
                                          For 3phase Delta-wired: Current for L1, L2, L3
                                          For 3phase WYE-wired: Current for L1, L2, L3, N"
                                   ::= { dataLogInletPoleEntry 4 }

dataLogMaxInletPoleCurrent                          OBJECT-TYPE
                                   SYNTAX        MilliAmps
                                   MAX-ACCESS    read-only
                                   STATUS        current
                                   DESCRIPTION
                                       "The Maximum value for the measurement period:
                                         The value of the current reported
                                       in MilliAmps.
                                          For Single Phase: Input Line Current
                                          For 3phase Delta-wired: Current for L1, L2, L3
                                          For 3phase WYE-wired: Current for L1, L2, L3, N"
                                   ::= { dataLogInletPoleEntry 5 }


dataLogMinInletPoleCurrent                        OBJECT-TYPE
                                   SYNTAX        MilliAmps
                                   MAX-ACCESS    read-only
                                   STATUS        current
                                   DESCRIPTION
                                       "The Minimum value for the measurement period:
                                        The value of the current reported
                                       in MilliAmps.
                                          For Single Phase: Input Line Current
                                          For 3phase Delta-wired: Current for L1, L2, L3
                                          For 3phase WYE-wired: Current for L1, L2, L3, N"
                                   ::= { dataLogInletPoleEntry 6 }

dataLogAvgInletPoleVoltage                          OBJECT-TYPE
                                   SYNTAX        MilliVolts
                                   MAX-ACCESS    read-only
                                   STATUS        current
                                   DESCRIPTION
                                       "The Average value for the measurement period:
                                        The value of the voltage reported
                                       in MilliVolts.
                                          For Single Phase: Input Line Voltage
                                          For 3phase Delta-wired: Voltages for L1-L2, L2-L3, L3-L1
                                          For 3phase WYE-wired: Voltages for L1-N, L2-N, L3-N"
                                   ::= { dataLogInletPoleEntry 7 }

dataLogMaxInletPoleVoltage                          OBJECT-TYPE
                                   SYNTAX        MilliVolts
                                   MAX-ACCESS    read-only
                                   STATUS        current
                                   DESCRIPTION
                                       "The Maximum value for the measurement period:
                                        The value of the voltage reported
                                       in MilliVolts.
                                          For Single Phase: Input Line Voltage
                                          For 3phase Delta-wired: Voltages for L1-L2, L2-L3, L3-L1
                                          For 3phase WYE-wired: Voltages for L1-N, L2-N, L3-N"
                                   ::= { dataLogInletPoleEntry 8 }

dataLogMinInletPoleVoltage                          OBJECT-TYPE
                                   SYNTAX        MilliVolts
                                   MAX-ACCESS    read-only
                                   STATUS        current
                                   DESCRIPTION
                                       "The Minimum value for the measurement period:
                                          The value of the voltage reported
                                       in MilliVolts.
                                          For Single Phase: Input Line Voltage
                                          For 3phase Delta-wired: Voltages for L1-L2, L2-L3, L3-L1
                                          For 3phase WYE-wired: Voltages for L1-N, L2-N, L3-N"
                                   ::= { dataLogInletPoleEntry 9 }


dataLogAvgInletPoleActivePower             OBJECT-TYPE
                                      SYNTAX        Watts
                                      MAX-ACCESS    read-only
                                      STATUS        current
                                      DESCRIPTION
                                         "This object has a valid value only for inline meters.
                                            If inlineMeter = 'No', then the value is invalid;
                                           In all other cases, it is the the Average value of the active power
                                           for the measurement period.
                                           The value is reported in Watts."
                                      ::= { dataLogInletPoleEntry 10 }

dataLogMaxInletPoleActivePower             OBJECT-TYPE
                                      SYNTAX        Watts
                                      MAX-ACCESS    read-only
                                      STATUS        current
                                      DESCRIPTION
                                         " This object has a valid value only for inline meters.
                                            If inlineMeter = 'No', then the value is invalid;
                                           In all other cases, it is the the Maximum value of the active power
                                           for the measurement period.
                                           The value is reported in Watts."
                                      ::= { dataLogInletPoleEntry 11 }

dataLogMinInletPoleActivePower             OBJECT-TYPE
                                      SYNTAX        Watts
                                      MAX-ACCESS    read-only
                                      STATUS        current
                                      DESCRIPTION
                                         " This object has a valid value only for inline meters.
                                            If inlineMeter = 'No', then the value is invalid;
                                           In all other cases, it is the the Minimum value of the active power
                                           for the measurement period.
                                           The value is reported in Watts."
                                      ::= { dataLogInletPoleEntry 12 }

dataLogAvgInletPoleApparentPower             OBJECT-TYPE
                                      SYNTAX        VoltAmps
                                      MAX-ACCESS    read-only
                                      STATUS        current
                                      DESCRIPTION
                                         "This object has a valid value only for inline meters.
                                            If inlineMeter = 'No', then the value is invalid;
                                           In all other cases, it is the the Average value of the apparent power
                                           for the measurement period.
                                           The value is reported in Volt-Amps"
                                      ::= { dataLogInletPoleEntry 13 }

dataLogMaxInletPoleApparentPower             OBJECT-TYPE
                                      SYNTAX        VoltAmps
                                      MAX-ACCESS    read-only
                                      STATUS        current
                                      DESCRIPTION
                                         " This object has a valid value only for inline meters.
                                            If inlineMeter = 'No', then the value is invalid;
                                           In all other cases, it is the the Maximum value of the apparent power
                                           for the measurement period.
                                           The value is reported in Volt-Amps"
                                      ::= { dataLogInletPoleEntry 14 }

dataLogMinInletPoleApparentPower             OBJECT-TYPE
                                      SYNTAX        VoltAmps
                                      MAX-ACCESS    read-only
                                      STATUS        current
                                      DESCRIPTION
                                         " This object has a valid value only for inline meters.
                                            If inlineMeter = 'No', then the value is invalid;
                                           In all other cases, it is the the Minimum value of the apparent power
                                           for the measurement period.
                                           The value is reported in Volt-Amps"
                                      ::= { dataLogInletPoleEntry 15 }

dataLogAvgInletPoleActiveEnergy              OBJECT-TYPE
                                      SYNTAX        WattHours
                                      MAX-ACCESS    read-only
                                      STATUS        current
                                      DESCRIPTION
                                         " This object has a valid value only for inline meters.
                                            If inlineMeter = 'No', then the value is invalid;
                                           In all other cases, it is the the Average value of the active energy
                                           for the measurement period.
                                           The value is reported in WattHours"
                                      ::= { dataLogInletPoleEntry 16 }

dataLogMaxInletPoleActiveEnergy              OBJECT-TYPE
                                      SYNTAX        WattHours
                                      MAX-ACCESS    read-only
                                      STATUS        current
                                      DESCRIPTION
                                         " This object has a valid value only for inline meters.
                                            If inlineMeter = 'No', then the value is invalid;
                                           In all other cases, it is the the Maximum value of the active energy
                                           for the measurement period.
                                           The value is reported in WattHours"
                                      ::= { dataLogInletPoleEntry 17 }

dataLogMinInletPoleActiveEnergy              OBJECT-TYPE
                                      SYNTAX        WattHours
                                      MAX-ACCESS    read-only
                                      STATUS        current
                                      DESCRIPTION
                                         " This object has a valid value only for inline meters.
                                            If inlineMeter = 'No', then the value is invalid;
                                           In all other cases, it is the the Minimum value of the active energy
                                           for the measurement period.
                                           The value is reported in WattHours"
                                      ::= { dataLogInletPoleEntry 18 }




-- the external sensors Data group

-- Implementation for external sensors

-- the external sensor table

-- The externalSensorTable table contains information on the external sensors.

dataLogExternalSensorTable     OBJECT-TYPE
                    SYNTAX        SEQUENCE OF DataLogExternalSensorEntryStruct
                    MAX-ACCESS    not-accessible
                    STATUS        current
                    DESCRIPTION
                        "A list of external sensor entries. The number of
                         entries is given by the value of externalSensorCount."
                    ::= { dataLogExternalSensor 1 }

dataLogExternalSensorEntry     OBJECT-TYPE
                    SYNTAX        DataLogExternalSensorEntryStruct
                    MAX-ACCESS    not-accessible
                    STATUS        current
                    DESCRIPTION
                        "An entry in the data log containing external sensor values"
                    INDEX         { dataLogIndex, dataLogExternalSensorIndex }
                    ::= { dataLogExternalSensorTable 1 }

DataLogExternalSensorEntryStruct ::= SEQUENCE { dataLogExternalSensorIndex                   Integer32,
                                                dataLogExternalSensorChanged                 DisplayString,
                                                dataLogExternalSensorState                   StateOfSensorEnumeration,
                                                dataLogAvgExternalSensorValue                Integer32,
                                                dataLogMaxExternalSensorValue                Integer32,
                                                dataLogMinExternalSensorValue                Integer32  }

dataLogExternalSensorIndex                    OBJECT-TYPE
                                   SYNTAX        Integer32(1..256)
                                   MAX-ACCESS    not-accessible
                                   STATUS        current
                                   DESCRIPTION
                                       "A unique value for each external sensor. Its value
                                        ranges between 1 and externalSensorCount."
                                   ::= { dataLogExternalSensorEntry 1 }

dataLogExternalSensorChanged                  OBJECT-TYPE
                                   SYNTAX        DisplayString
                                   MAX-ACCESS    read-only
                                   STATUS        current
                                   DESCRIPTION
                                       "Indicates whether there has been a change in the sensor type/subtype/channel number for this sensorID.
                                        This can occur if sensorIDs have been reassigned as a result of
                                           a GUI operation or a SET operation on reorderexternalSensorTableEntries.

                                        Format: SerialNumber=xxxxxxxx; SensorType=dd; SensorSubType=d; ChannelNumber=d
                                        SensorSubType and ChannelNumber are present only if NewSensorType=onOff
                                        If there was no change from the previous sample, then
                                              this string is empty.

                                        Examples:
                                             Sensor changed to Temperature:
                                                         SerialNumber=AEI8160083; SensorType=10;
                                             Sensor changed to onOff/SmokeDetection:
                                                         SerialNumber=AEI8160083; SensorType=14; SensorSubType= 18; ChannelNumber=1
                                             Sensor Channel Number changed:
                                                         SerialNumber=AEI8160083; SensorType=14; SensorSubType= 18; ChannelNumber=2
                                             Sensor SubType changed:
                                                         SerialNumber=AEI8160083; SensorType=14; SensorSubType= 19; ChannelNumber=2
                                          "
                                   ::= { dataLogExternalSensorEntry 2 }

dataLogExternalSensorState                          OBJECT-TYPE
                                   SYNTAX        StateOfSensorEnumeration
                                   MAX-ACCESS    read-only
                                   STATUS        current
                                   DESCRIPTION
                                       "The sensor state.
                                       "
                                   ::= { dataLogExternalSensorEntry 3 }

dataLogAvgExternalSensorValue                      OBJECT-TYPE
                                   SYNTAX        Integer32
                                   MAX-ACCESS    read-only
                                   STATUS        current
                                   DESCRIPTION
                                       "The Average of the sensor values
                                        Does not apply (gets will return 0)
                                           to onOff, trip, vibration, waterDetection,
                                           smokeDetection sensors.
                                        This value is not valid if dataLogExternalSensorState is unavailable(-1).
                                       "
                                   ::= { dataLogExternalSensorEntry 4 }

dataLogMaxExternalSensorValue                      OBJECT-TYPE
                                   SYNTAX        Integer32
                                   MAX-ACCESS    read-only
                                   STATUS        current
                                   DESCRIPTION
                                       "The Maximum of the sensor values
                                        Does not apply (gets will return 0)
                                           to onOff, trip, vibration, waterDetection,
                                           smokeDetection sensors
                                        This value is not valid if dataLogExternalSensorState is unavailable(-1).
                                       "
                                   ::= { dataLogExternalSensorEntry 5 }

dataLogMinExternalSensorValue                      OBJECT-TYPE
                                   SYNTAX        Integer32
                                   MAX-ACCESS    read-only
                                   STATUS        current
                                   DESCRIPTION
                                       "The Minimum of the sensor values.
                                        Does not apply (gets will return 0)
                                           to onOff, trip, vibration, waterDetection,
                                           smokeDetection sensors
                                        This value is not valid if dataLogExternalSensorState is unavailable(-1).
                                       "
                                   ::= { dataLogExternalSensorEntry 6 }




-- Start the traps

rebootStarted             NOTIFICATION-TYPE
                          OBJECTS { objectName,
                                    objectInstance,
                                    userName }
                          STATUS current
                          DESCRIPTION
                              "The reboot process has started"
                          ::= { traps 1 }

rebootCompleted           NOTIFICATION-TYPE
                          OBJECTS { objectName,
                                    objectInstance }
                          STATUS current
                          DESCRIPTION
                              "The reboot process is complete"
                          ::= { traps 2 }

userLogin                 NOTIFICATION-TYPE
                          OBJECTS { objectName,
                                    objectInstance,
                                    userName,
                                    ipAddress }
                          STATUS current
                          DESCRIPTION
                              "A user logged in"
                          ::= { traps 3 }

userLogout                NOTIFICATION-TYPE
                          OBJECTS { objectName,
                                    objectInstance,
                                    userName,
                                    ipAddress }
                          STATUS current
                          DESCRIPTION
                              "A user logged out"
                          ::= { traps 4 }

userAuthenticationFailure NOTIFICATION-TYPE
                          OBJECTS { objectName,
                                    objectInstance,
                                    userName,
                                    ipAddress }
                          STATUS current
                          DESCRIPTION
                              "A user authentication attempt failed"
                          ::= { traps 5 }

userSessionTimeout        NOTIFICATION-TYPE
                          OBJECTS { objectName,
                                    objectInstance,
                                    userName,
                                    ipAddress }
                          STATUS current
                          DESCRIPTION
                              "A user timed out from the device"
                          ::= { traps 8 }

userAdded                 NOTIFICATION-TYPE
                          OBJECTS { objectName,
                                    objectInstance,
                                    userName,
                                    targetUser }
                          STATUS current
                          DESCRIPTION
                              "A user was added to the system"
                          ::= { traps 11 }

userModified              NOTIFICATION-TYPE
                          OBJECTS { objectName,
                                    objectInstance,
                                    userName,
                                    targetUser }
                          STATUS current
                          DESCRIPTION
                              "A user account was modified"
                          ::= { traps 12 }

userDeleted               NOTIFICATION-TYPE
                          OBJECTS { objectName,
                                    objectInstance,
                                    userName,
                                    targetUser }
                          STATUS current
                          DESCRIPTION
                              "A user was deleted from the system"
                          ::= { traps 13 }

groupAdded                NOTIFICATION-TYPE
                          OBJECTS { objectName,
                                    objectInstance,
                                    userName,
                                    groupName }
                          STATUS current
                          DESCRIPTION
                              "A group was added to the system"
                          ::= { traps 14 }

groupModified             NOTIFICATION-TYPE
                          OBJECTS { objectName,
                                    objectInstance,
                                    userName,
                                    groupName }
                          STATUS current
                          DESCRIPTION
                              "A group was modified"
                          ::= { traps 15 }


groupDeleted              NOTIFICATION-TYPE
                          OBJECTS { objectName,
                                    objectInstance,
                                    userName,
                                    groupName }
                          STATUS current
                          DESCRIPTION
                              "A group was deleted from the system"
                          ::= { traps 16 }

deviceUpdateStarted       NOTIFICATION-TYPE
                          OBJECTS { objectName,
                                    objectInstance,
                                    userName,
                                    ipAddress,
                                    imageVersion }
                          STATUS current
                          DESCRIPTION
                              "The device update has started"
                          ::= { traps 20 }

userBlocked               NOTIFICATION-TYPE
                          OBJECTS { objectName,
                                    objectInstance,
                                    userName,
                                    ipAddress }
                          STATUS current
                          DESCRIPTION
                              "A blocked user tried to log in"
                          ::= { traps 22 }

powerControl              NOTIFICATION-TYPE
                          OBJECTS { objectName,
                                    objectInstance,
                                    userName,
                                    ipAddress,
                                    outletLabel,
                                    outletOperationalState }
                          STATUS current
                          DESCRIPTION
                              "An outlet has been switched"
                          ::= { traps 23 }

userPasswordChanged       NOTIFICATION-TYPE
                          OBJECTS { objectName,
                                    objectInstance,
                                    userName,
                                    targetUser,
                                    ipAddress }
                          STATUS current
                          DESCRIPTION
                              "A user password was changed"
                          ::= { traps 24 }

passwordSettingsChanged   NOTIFICATION-TYPE
                          OBJECTS { objectName,
                                    objectInstance,
                                    userName,
                                    status }
                          STATUS current
                          DESCRIPTION
                              "Strong password settings changed "
                          ::= { traps 28 }

-- Start new event to support RP products

firmwareFileDiscarded     NOTIFICATION-TYPE
                          OBJECTS { objectName,
                                    objectInstance,
                                    userName }
                          STATUS current
                          DESCRIPTION
                              "A firmware file discarded "
                          ::= { traps 36 }

firmwareValidationFailed  NOTIFICATION-TYPE
                          OBJECTS { objectName,
                                    objectInstance,
                                    userName }
                          STATUS current
                          DESCRIPTION
                              "A firmware validation failed "
                          ::= { traps 38 }

securityViolation         NOTIFICATION-TYPE
                          OBJECTS { objectName,
                                    objectInstance,
                                    userName,
                                    ipAddress }
                          STATUS current
                          DESCRIPTION
                              "Security violation."
                          ::= { traps 39 }

logFileCleared            NOTIFICATION-TYPE
                          OBJECTS { objectName,
                                    objectInstance,
                                    userName }
                          STATUS current
                          DESCRIPTION
                              "The log file has been cleared."
                          ::= { traps 41 }

-- Sensor threshold traps
thresholdAlarm                       NOTIFICATION-TYPE
                                     OBJECTS { objectName,
                                               objectInstance,
                                               ipAddress,
                                               sensorDescr,
                                               thresholdDescr,
                                               thresholdSeverity,
                                               thresholdEventType,
                                               sensorIdentificationString,
                                               thresholdValue,
                                               sensorValue  }
                                     STATUS current
                                     DESCRIPTION
                                         "Configured sensor theshold event. The 'thresholdEventType' variable will indicate whether or not
                                          the threshold triggered or cleared.
                                          thresholdValue and sensorValue have valid values only for external temperature and humidity sensors.
                                          "
                                     ::= { traps 45 }

-- Outlet Grouping Connectivity Application traps
outletGroupingConnectivityLost       NOTIFICATION-TYPE
                                     OBJECTS { objectName,
                                               objectInstance,
                                               ipAddress,
                                               slaveIpAddress }
                                     STATUS current
                                     DESCRIPTION
                                         "Master PDU lost contact with the slave PDU in an outlet grouping configuration."
                                     ::= { traps 50 }

-- circuit Breaker tripped/recovered traps
circuitBreakerTripped        NOTIFICATION-TYPE
                                     OBJECTS { objectName,
                                               objectInstance,
                                               ipAddress,
                                               circuitBreakerLabel }
                                     STATUS current
                                     DESCRIPTION
                                         "Circuit Breaker Tripped."
                                     ::= { traps 51 }

circuitBreakerRecovered        NOTIFICATION-TYPE
                                     OBJECTS { objectName,
                                               objectInstance,
                                               ipAddress,
                                               circuitBreakerLabel }
                                     STATUS current
                                     DESCRIPTION
                                         "Circuit Breaker Recovered."
                                     ::= { traps 52 }


bulkConfigurationSaved        NOTIFICATION-TYPE
                                     OBJECTS { objectName,
                                               objectInstance,
                                               ipAddress }
                                     STATUS current
                                     DESCRIPTION
                                         "Bulk Configuration saved."
                                     ::= { traps 53 }

bulkConfigurationCopied        NOTIFICATION-TYPE
                                     OBJECTS { objectName,
                                               objectInstance,
                                               ipAddress }
                                     STATUS current
                                     DESCRIPTION
                                         "Bulk Configuration saved."
                                     ::= { traps 54 }


environmentalSensorsConnectivityLost        NOTIFICATION-TYPE
                                     OBJECTS { objectName,
                                               objectInstance,
                                               ipAddress,
                                               sensorDescr,
                                               externalSensorNumber,
                                               externalSensorType,
                                               externalSensorName,
                                               externalSensorChannelNumber,
                                               externalBinarySensorSubtype,
                                               externalSensorSerialNumber  }
                                     STATUS current
                                     DESCRIPTION
                                         "lost connectivity to environmental Sensors"
                                     ::= { traps 55 }



externalOnOffSensorStateChange           NOTIFICATION-TYPE
                                     OBJECTS {
                                               objectName,
                                               objectInstance,
                                               ipAddress,
                                               externalSensorNumber,
                                               externalSensorType,
                                               externalSensorName,
                                               externalSensorChannelNumber,
                                               externalBinarySensorSubtype,
                                               externalSensorState,
                                               oldSensorState,
                                               externalSensorSerialNumber
 }
                                     STATUS current
                                     DESCRIPTION
                                         "External OnOff Sensor State Change."
                                     ::= { traps 56 }


environmentalSensorsConnectivityRestored        NOTIFICATION-TYPE
                                           OBJECTS { objectName,
                                               objectInstance,
                                               ipAddress,
                                               externalSensorNumber,
                                               externalSensorType,
                                               externalSensorName,
                                               externalSensorChannelNumber,
                                               externalBinarySensorSubtype,
                                               externalSensorSerialNumber }
                                             STATUS current
                                          DESCRIPTION
                                         " connectivity to environmental Sensor was restored"
                                     ::= { traps 57 }


voltageMeasurementError        NOTIFICATION-TYPE
                                           OBJECTS { objectName,
                                               objectInstance,
                                               ipAddress,
                                               psocNumber
                                              }
                                             STATUS current
                                          DESCRIPTION
                                         " voltage measurement error, a Psoc (Outlet Controller) reported  zero voltage and non-zero current.
                                           Voltage, power and energy measurements may be in error "
                                     ::= { traps 58 }


fipsModeEnabled   NOTIFICATION-TYPE
                          OBJECTS { objectName,
                                    objectInstance,
                                    userName
                                    }
                          STATUS current
                          DESCRIPTION
                              "FIPS Mode Enabled "
                          ::= { traps 59 }


fipsModeDisabled   NOTIFICATION-TYPE
                          OBJECTS { objectName,
                                    objectInstance,
                                    userName
                                    }
                          STATUS current
                          DESCRIPTION
                              "FIPS Mode Disabled "
                          ::= { traps 60 }


managingenvironmentalSensor       NOTIFICATION-TYPE
                                           OBJECTS { objectName,
                                               objectInstance,
                                               ipAddress,
                                               sensorDescr,
                                               externalSensorNumber,
                                               externalSensorType,
                                               externalSensorName,
                                               externalSensorChannelNumber,
                                               externalBinarySensorSubtype,
                                               externalSensorSerialNumber }
                                             STATUS current
                                          DESCRIPTION
                                         " begin managing environmental Sensor "
                                     ::= { traps 61 }



unmanagingenvironmentalSensor       NOTIFICATION-TYPE
                                           OBJECTS { objectName,
                                               objectInstance,
                                               ipAddress,
                                               sensorDescr,
                                               externalSensorNumber,
                                               externalSensorType,
                                               externalSensorName,
                                               externalSensorChannelNumber,
                                               externalBinarySensorSubtype,
                                               externalSensorSerialNumber }
                                             STATUS current
                                          DESCRIPTION
                                         " cease managing environmental Sensor"
                                     ::= { traps 62 }

ipmiOverLANEnabled   NOTIFICATION-TYPE
                          OBJECTS { objectName,
                                    objectInstance,
                                    userName
                                    }
                          STATUS current
                          DESCRIPTION
                              "IPMI Over LAN Mode has been Enabled "
                          ::= { traps 63 }


ipmiOverLANDisabled   NOTIFICATION-TYPE
                          OBJECTS { objectName,
                                    objectInstance,
                                    userName
                                    }
                          STATUS current
                          DESCRIPTION
                              "IPMI Over LAN Mode has been Disabled "
                          ::= { traps 64 }



END
