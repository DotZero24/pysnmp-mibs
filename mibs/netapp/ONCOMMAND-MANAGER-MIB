-- ============================= --
    -- OnCommand Custom MIB --
    -- ============================= --

    -- Version 9.4

    -- Copyright (c) 2018 NetApp, Inc.
    -- All rights reserved.

    -- This NetApp OnCommand SNMP Management Information Base
    -- (Specification) embodies NetApp's confidential
    -- and proprietary intellectual property.  NetApp
    -- retains all title and ownership in the Specification,
    -- including any revisions.

    -- This Specification is supplied "AS IS," and NetApp
    -- makes no warranty, either express or implied, as to the use,
    -- operation, condition, or performance of the Specification.

    -- Agent support for this MIB is not available yet.

    ONCOMMAND-MANAGER-MIB DEFINITIONS ::= BEGIN

    IMPORTS
        netappOnCommand
            FROM NETAPP-MIB
        OBJECT-TYPE
            FROM RFC-1212;

    --  This MIB module uses the extended OBJECT-TYPE macro as
    --  defined in RFC-1212


    --  MIB-II (same prefix as MIB-I)


    -- textual conventions

    DisplayString ::=
        OCTET STRING
    -- This data type is used to model textual information taken
    -- from the NVT ASCII character set.  By convention, objects
    -- with this syntax are declared as having
    --
    --      SIZE (0..255)

    -- the OnCommand MIB

    -- root for all objects for OnCommand

    -- This identifier is declared in the NETAPP-MIB which is imported above
    -- netappOnCommand    OBJECT IDENTIFIER ::= { netapp 5 }

    --
    -- This is the tree under which values for the OnCommand Unified Manager are specified.
    --

    netappOnCommandUnifiedManager OBJECT IDENTIFIER ::= { netappOnCommand 1 }

    ocumSystemId    OBJECT-TYPE
    SYNTAX      DisplayString
    ACCESS      read-only
    STATUS      mandatory
    DESCRIPTION
            "System ID of the OnCommand Unified Manager server installation."
    ::= { netappOnCommandUnifiedManager 1 }

    ocumEvent OBJECT IDENTIFIER ::= { netappOnCommandUnifiedManager 2 }

    ocumEventName   OBJECT-TYPE
    SYNTAX      DisplayString
    ACCESS      read-only
    STATUS      mandatory
    DESCRIPTION
            "Display name of the event. e.g. Volume Full."
    ::= { ocumEvent 1 }

    ocumEventSeverity   OBJECT-TYPE
    SYNTAX          INTEGER {
                    warning(3),
                    error(4),
                    critical(5)
                }
    ACCESS          read-only
    STATUS          mandatory
    DESCRIPTION
                "Severity of the event."
    ::= { ocumEvent 2 }

    ocumEventImpactLevel   OBJECT-TYPE
    SYNTAX          INTEGER {
                    event(1),
                    risk(2),
                    incident(3)
                }
    ACCESS          read-only
    STATUS          mandatory
    DESCRIPTION
                "Impact level of the event."
    ::= { ocumEvent 3 }

    ocumEventTimestamp    OBJECT-TYPE
    SYNTAX            INTEGER
    ACCESS            read-only
    STATUS            mandatory
    DESCRIPTION
                "Event creation timestamp represented as the
                 number of seconds since 00:00:00 UTC,
                 January 1, 1970."
    ::= { ocumEvent 4 }

    ocumEventMessage    OBJECT-TYPE
    SYNTAX        DisplayString
    ACCESS        read-only
    STATUS        mandatory
    DESCRIPTION
            "Fixed format message describing condition that caused
             the event."
    ::= { ocumEvent 5 }

    ocumEventMessageDetails    OBJECT-TYPE
    SYNTAX        DisplayString
    ACCESS        read-only
    STATUS        mandatory
    DESCRIPTION
            "More detailed message about the event if available."
    ::= { ocumEvent 6 }

    ocumEventSourceResourceKey  OBJECT-TYPE
    SYNTAX          DisplayString
    ACCESS          read-only
    STATUS          optional
    DESCRIPTION
            "Resource key of the object that is source of the event."
    ::= { ocumEvent 7 }

    ocumEventSourceFullName    OBJECT-TYPE
    SYNTAX        DisplayString
    ACCESS        read-only
    STATUS        mandatory
    DESCRIPTION
            "Full name of the object."
    ::= { ocumEvent 8 }

    ocumEventSourceType    OBJECT-TYPE
    SYNTAX      INTEGER {
                unknown(1),
                mgmtStation(2),
                cluster(3),
                clusterNode(4),
                vserver(5),
                volume(6),
                qtree(7),
                lun(8),
                aggregate(9),
                disk(10),
                port(11),
                lif(12),
                storageService(13),
                igroup(14),
                fcpTarget(15),
                mirror(16),
                portSet(17),
                exportPolicy(18),
                userQuota(19),
                storageClass(20),
                switch(21),
                bridge(22),
                nodeSwitchConnection(23),
                metroClusterRelationship(24),
                interSwitchConnection(25),
                switchBridgeConnection(26),
                bridgeStackConnection(27),
                interNodeConnection(28),
                nodeBridgeConnection(29),
                nodeStackConnection(30),
                objectstoreConfig(32)
            }
    ACCESS        read-only
    STATUS        mandatory
    DESCRIPTION
            "Type of the object."
    ::= { ocumEvent 9 }

    ocumEventSourceHealthStatus    OBJECT-TYPE
    SYNTAX      INTEGER {
                normal(1),
                warning(2),
                error(3),
                critical(4)
            }
    ACCESS        read-only
    STATUS        mandatory
    DESCRIPTION
            "Status of the object."
    ::= { ocumEvent 10 }

    ocumEventSourceScopedResourceKey   OBJECT-TYPE
    SYNTAX      DisplayString
    ACCESS      read-only
    STATUS      mandatory
    DESCRIPTION
            "Resource key of the Vserver, Node, or Cluster the event source
            is scoped to."
    ::= { ocumEvent 11 }

    ocumEventSourceScopedFullName    OBJECT-TYPE
    SYNTAX        DisplayString
    ACCESS        read-only
    STATUS        mandatory
    DESCRIPTION
            "Full name of the Vserver, Node, or Cluster the event source
            is scoped to."
    ::= { ocumEvent 12 }

    ocumEventSourceClusterResourceKey OBJECT-TYPE
    SYNTAX        DisplayString
    ACCESS        read-only
    STATUS        mandatory
    DESCRIPTION
            "Resource Key for the cluster the event source is on."
    ::= { ocumEvent 13 }

    ocumEventSourceClusterFullName OBJECT-TYPE
    SYNTAX        DisplayString
    ACCESS        read-only
    STATUS        mandatory
    DESCRIPTION
            "Full name of the cluster the event source is on."
    ::= { ocumEvent 14 }

    ocumEventState OBJECT-TYPE
    SYNTAX          INTEGER {
                    new(1),
                    acknowledged(2),
                    resolved(3),
                    obsolete_um(4)
                }
    ACCESS          read-only
    STATUS          mandatory
    DESCRIPTION
                "State of the event."
    ::= { ocumEvent 15 }

    ocumTestAlert OBJECT IDENTIFIER ::= { netappOnCommandUnifiedManager 3 }

    ocumTestAlertTimestamp   OBJECT-TYPE
    SYNTAX            INTEGER
    ACCESS            read-only
    STATUS            mandatory
    DESCRIPTION
                "Test alert creation timestamp represented as the
                 number of seconds since 00:00:00 UTC,
                 January 1, 1970."
    ::= { ocumTestAlert 1 }

    -- =================
    -- Traps sent by OnCommand Unified Manager
    -- =================

    -- aggregate events

    ocumEvtAggregate64BitUpgrade    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "An aggregate being managed by OnCommand Unified Manager server has
         been migrated from 32-bit to 64-bit.
         Variable ocumEventSourceResourceKey identifies the aggregate."
    ::= 13000

    ocumEvtAggregateDiscovered    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A new aggregate has been discovered by OnCommand Unified Manager server."
    ::= 13010

    -- traps for aggregate state

    ocumEvtAggregateStateFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The aggregate being managed by OnCommand Unified Manager server
         has failed. Variable ocumEventSourceResourceKey identifies the
         aggregate."
    ::= 13020

    ocumEvtAggregateStateRestricted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The aggregate being managed by OnCommand Unified Manager server
         is restricted. Variable ocumEventSourceResourceKey identifies the
         aggregate."
    ::= 13021

    ocumEvtAggregateStateOnline    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The aggregate being managed by OnCommand Unified Manager server
         is online. Variable ocumEventSourceResourceKey identifies the
         aggregate."
    ::= 13022

    ocumEvtAggregateStateOffline    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The aggregate being managed by OnCommand Unified Manager server
         is offline. Variable ocumEventSourceResourceKey identifies the
         aggregate."
    ::= 13023

    -- traps for aggregate raid state

    ocumEvtAggregateRaidStateNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The RAID state of the aggregate being managed by OnCommand Unified Manager server
         is normal. Variable ocumEventSourceResourceKey identifies the
         aggregate."
    ::= 13030

    ocumEvtAggregateRaidStateDegraded    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The RAID state of the aggregate being managed by OnCommand Unified Manager server
         is degraded. Variable ocumEventSourceResourceKey identifies the
         aggregate."
    ::= 13031

    ocumEvtAggregateRaidStateReconstructing    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The RAID state of the aggregate being managed by OnCommand Unified Manager server
         is reconstructing. Variable ocumEventSourceResourceKey identifies the
         aggregate."
    ::= 13032

    ocumEvtAggregateSpaceOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization on the aggregate being
         managed by OnCommand Unified Manager server is below its
         'neralyFull' threshold. Variable
         ocumEventSourceResourceKey identifies the aggregrate."
    ::= 13040

    ocumEvtAggregateNearlyFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization by an aggregate
         being managed by OnCommand Unified Manager server has crossed
         'nearlyFull' threshold.
         Variable ocumEventSourceResourceKey identifies the volume."
    ::= 13041

    ocumEvtAggregateFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization by an aggregate
         being managed by OnCommand Unified Manager server has crossed
         'full' threshold.
         Variable ocumEventSourceResourceKey identifies the aggregate."
    ::= 13042

    ocumEvtAggregateDaysUntilFullNotSoon    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The aggregate will not be full soon."
    ::= 13050

    ocumEvtAggregateDaysUntilFullSoon    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The aggregate will be full soon."
    ::= 13051

    -- aggregate subscription events

    ocumEvtAggregateNotOvercommited    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The aggregate being managed by OnCommand Unified Manager server
         is below its 'almostOvercommitted' threshold. Variable
         ocumEventSourceResourceKey identifies the aggregrate."
    ::= 13060

    ocumEvtAggregateAlmostOvercommitted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The aggregate being managed by OnCommand Unified Manager server
         has crossed the 'almostOvercommitted' threshold.
         Variable ocumEventSourceResourceKey identifies the aggregate."
    ::= 13061

    ocumEvtAggregateOvercommitted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The aggregate being managed by OnCommand Unified Manager server
         has crossed the 'overcommitted' threshold.
         Variable ocumEventSourceResourceKey identifies the aggregate."
    ::= 13062

    -- aggregate snap reserve events

    ocumEvtAggregateSnapReserveOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The snapshot reserve usage of an aggregate being
         managed by OnCommand Unified Manager server is below its
         'almostFull' threshold. Variable
         ocumEventSourceResourceKey identifies the aggregrate."
    ::= 13070

    ocumEvtAggregateSnapReserveFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The snapshot reserve usage of an aggregate
         being managed by OnCommand Unified Manager server has crossed
         'full' threshold.
         Variable ocumEventSourceResourceKey identifies the aggregate."
    ::= 13071

    ocumEvtAggregateGrowthRateOk    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The Aggregate Growth Rate is Normal."
    ::= 13080

    ocumEvtAggregateGrowthRateAbnormal    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The Aggregate Growth Rate is Abnormal."
    ::= 13081

    ocumEvtAggregateDeleted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "An aggregate that OnCommand Unified Manager server has been managing is no
        longer present."
    ::= 13090

    ocumEvtAggregateRenamed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The Aggregate was renamed."
    ::= 13100


    ocumEvtMetroClusterAggregateLeftBehindFixed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The Aggregate that was left behind during MetroCluster switchback operation has switched back to the owner cluster."
    ::= 13110

    ocumEvtMetroClusterAggregateLeftBehind    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The Aggregate was left behind during MetroCluster switchback operation."
    ::= 13111


    -- cluster events

    -- disk events

    ocumEvtClusterUnassignedDisksNone    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "No unassigned disk is discovered."
    ::= 13210

    ocumEvtClusterUnassignedDisksSome    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Unassigned disks are discovered."
    ::= 13211

    ocumEvtDisksSparesAvailable    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "There are spare disks available on the cluster being monitored
         by OnCommand Unified Manager server. The ocumEventSourceResourceKey is that of the cluster."
    ::= 13220

    ocumEvtDisksNoSpares    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "There are no spare disks on the cluster being
         monitored by OnCommand Unified Manager server.
         The ocumEventSourceResourceKey is that of the cluster."
    ::= 13221

    ocumEvtDisksNoneFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "There are no failed disks on the cluster being
         monitored by OnCommand Unified Manager server."
    ::= 13230

    ocumEvtDisksSomeFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "There are some failed disks on the cluster being monitored
         by OnCommand Unified Manager server."
    ::= 13231

    ocumEvtClusterRemoved    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }

    DESCRIPTION
        "A managed cluster was removed."
    ::= 13240

    ocumEvtClusterAddFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }

    DESCRIPTION
        "Adding a cluster failed."
    ::= 13241

    ocumEvtClusterRenamed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The cluster was renamed."
    ::= 13250

    ocumEvtClusterReachable    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The cluster managed by OnCommand Unified Manager server is reachable."
    ::= 13270

    ocumEvtClusterUnreachable    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The cluster managed by OnCommand Unified Manager server is not reachable."
    ::= 13271

        ocumEvtClusterMonitoringSucceeded    TRAP-TYPE
        ENTERPRISE    netappOnCommandUnifiedManager
        VARIABLES    {
                    ocumSystemId,
                    ocumEventName,
                    ocumEventSeverity,
                    ocumEventImpactLevel,
                    ocumEventTimestamp,
                    ocumEventMessage,
                    ocumEventMessageDetails,
                    ocumEventSourceResourceKey,
                    ocumEventSourceFullName,
                    ocumEventSourceType,
                    ocumEventSourceHealthStatus,
                    ocumEventSourceScopedResourceKey,
                    ocumEventSourceScopedFullName,
                    ocumEventSourceClusterResourceKey,
                    ocumEventSourceClusterFullName,
                ocumEventState
                }
        DESCRIPTION
            "The cluster managed by OnCommand Unified Manager server was monitored."
        ::= 13280

        ocumEvtClusterMonitoringFailed    TRAP-TYPE
        ENTERPRISE    netappOnCommandUnifiedManager
        VARIABLES    {
                    ocumSystemId,
                    ocumEventName,
                    ocumEventSeverity,
                    ocumEventImpactLevel,
                    ocumEventTimestamp,
                    ocumEventMessage,
                    ocumEventMessageDetails,
                    ocumEventSourceResourceKey,
                    ocumEventSourceFullName,
                    ocumEventSourceType,
                    ocumEventSourceHealthStatus,
                    ocumEventSourceScopedResourceKey,
                    ocumEventSourceScopedFullName,
                    ocumEventSourceClusterResourceKey,
                    ocumEventSourceClusterFullName,
                ocumEventState
                }
        DESCRIPTION
            "The cluster managed by OnCommand Unified Manager server could not be monitored."
        ::= 13281

    -- node traps

    ocumEvtClusterNodeAdded    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A node was added to this cluster."
    ::= 13400

    ocumEvtClusterNodeRemoved    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A node was removed from this cluster."
    ::= 13410

    ocumEvtClusterNodeRenamed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A node in this cluster is renamed."
    ::= 13411

    -- SFO Interconnect events

    ocumEvtSfoInterconnectUp    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The SFO interconnect hardware attached to the clustered
         node being monitored by OnCommand Unified Manager server is up."
    ::= 13420

    ocumEvtSfoInterconnectOneOrMoreLinksDown    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The SFO interconnect hardware attached to the clustered
         node being monitored by OnCommand Unified Manager server
         has one link down"
    ::= 13421

    -- SFO settings events

    ocumEvtSfoSettingsEnabled    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The SFO settings have been enabled on the node being
         monitored by OnCommand Unified Manager server."
    ::= 13430

    ocumEvtSfoSettingsNotConfigured    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The SFO settings have not been configured on the node being
         monitored by OnCommand Unified Manager server."
    ::= 13431

    ocumEvtSfoSettingsDisabled    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The SFO settings have been disabled on the node being
         monitored by OnCommand Unified Manager server."
    ::= 13432

    ocumEvtSfoStateConnected    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Node is connected to partner node."
    ::= 13440

    ocumEvtSfoStateTakeover    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Taken over the partner node."
    ::= 13441

    ocumEvtSfoStatePartialGiveback    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Giveback to partner node partially completed."
    ::= 13442

    ocumEvtSfoNodeStatusUp    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The firmware status of the node is up."
    ::= 13450

    ocumEvtSfoNodeStatusDown    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The firmware status of the node is down."
    ::= 13451

    ocumEvtSfoTakeoverPossible    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage Takeover of nodes in the SFO pair is possible."
    ::= 13460

    ocumEvtSfoTakeoverNotPossible    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage Takeover of nodes in the SFO pair is not possible."
    ::= 13461

    -- fan events

    ocumEvtFansNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The fans on the monitored node are functioning normally."
    ::= 13470

    ocumEvtFansOneOrMoreFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "One or more fans have failed on the node being
         monitored by OnCommand Unified Manager server."
    ::= 13471

    -- NVRAM Battery events

    ocumEvtNvramBatteryOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The NVRAM battery on the node monitored
         by OnCommand Unified Manager server is fine."
    ::= 13480

    ocumEvtNvramBatteryLow    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The NVRAM battery on the node monitored
         by OnCommand Unified Manager server has been partially discharged."
    ::= 13481

    ocumEvtNvramBatteryOverCharged    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The NVRAM battery on the node monitored
        by OnCommand Unified Manager server has been overcharged."
    ::= 13482

    ocumEvtNvramBatteryDischarged    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The NVRAM battery on the node monitored by
         OnCommand Unified Manager server has been fully discharged."
    ::= 13483

    -- power supply events

    ocumEvtPowerSupplyOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The power supplies on the monitored node are functioning
         normally."
    ::= 13490

    ocumEvtPowerSupplyOneOrMoreFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "There are one or more power supplies failed on the node being
         monitored by OnCommand Unified Manager server."
    ::= 13491

    ocumEvtClusterNodeRootVolumeSpaceOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization on the root volume of the monitored node is normal."
    ::= 13500

    ocumEvtClusterNodeRootVolumeSpaceNearlyFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization on the root volume of the monitored node has breached the nearly full limit."
    ::= 13501

    -- Net Port events

    ocumEvtPortStatusUp    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Status of the port of a node that OnCommand Unified Manager server has been
        managing is up."
    ::= 13510

    ocumEvtPortStatusDown    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Status of the port of a node that OnCommand Unified Manager server has been
        managing is down."
    ::= 13511

    -- flash card events

    ocumEvtFlashCardOnline    TRAP-TYPE
    ENTERPRISE    netappOnCommandUnifiedManager
    VARIABLES        {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The flash card monitored by OnCommand Unified Manager is online."
    ::= 13520

    ocumEvtFlashCardOffline    TRAP-TYPE
    ENTERPRISE    netappOnCommandUnifiedManager
    VARIABLES        {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                        }
    DESCRIPTION
        "The flash card monitored by OnCommand Unified Manager is offline."
    ::= 13521

    -- service processor events

    ocumEvtServiceProcessorOnline    TRAP-TYPE
    ENTERPRISE    netappOnCommandUnifiedManager
    VARIABLES        {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The service processor monitored by OnCommand Unified Manager is online."
    ::= 13522

    ocumEvtServiceProcessorOffline    TRAP-TYPE
    ENTERPRISE    netappOnCommandUnifiedManager
    VARIABLES        {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                        }
    DESCRIPTION
        "The service processor monitored by OnCommand Unified Manager is offline."
    ::= 13523

    ocumEvtServiceProcessorNotConfigured    TRAP-TYPE
    ENTERPRISE    netappOnCommandUnifiedManager
    VARIABLES        {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                        }
    DESCRIPTION
        "The service processor monitored by OnCommand Unified Manager is not configured."
    ::= 13524

    -- Efficiency Policy

    ocumEvtEfficiencyPolicyEnabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Efficiency Policy Enabled."
    ::= 13600

    ocumEvtEfficiencyPolicyDisabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Efficiency Policy Disabled."
    ::= 13601

    -- logical interface events

    ocumEvtLifStatusUp    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Status of the logical interface that OnCommand Unified Manager server has been
        managing is up."
    ::= 13700

    ocumEvtLifStatusDown    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Status of the logical interface that OnCommand Unified Manager server has been
        managing is down."
    ::= 13701

    ocumEvtLifMigrated    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Logical interface that OnCommand Unified Manager server has been managing migrated to a different node."
    ::= 13702

    ocumEvtLifFailoverPossible    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The failover policy is currently enabled."
    ::= 13703

    ocumEvtLifFailoverNotPossible    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The failover policy is currently disabled."
    ::= 13704

    ocumEvtLifNoRouteConfigured    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Logical interface No Route Configured"
    ::= 13705

    ocumEvtLifNotAtHomePort    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Logical interface Not At Home Port"
    ::= 13706

    ocumEvtLifAtHomePort    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Logical interface At Home Port"
    ::= 13707

    -- LUN events

    ocumEvtLunSnapshotOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A snapshot can be taken of the volume containing the LUN.
         Variable ocumEventSourceResourceKey identifies the volume."
    ::= 13800

    ocumEvtLunSnapshotNotPossible    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A snapshot of the volume containing this LUN cannot be taken
         because required space is not available for this operation.
         Variable ocumEventSourceResourceKey identifies the volume."
    ::= 13801

    ocumEvtLunSpaceReservationEnabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "LUN space reserve was enabled."
    ::= 13810

    ocumEvtLunSpaceReservationDisabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "LUN space reserve was disabled."
    ::= 13811

    ocumEvtLunOnline    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The LUN is online. Variable ocumEventSourceResourceKey identifies the LUN."
    ::= 13820

    ocumEvtLunOffline    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The LUN is offline. Variable ocumEventSourceResourceKey identifies the LUN."
    ::= 13821

    ocumEvtLunMultipleActivePath    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The event indicates that there are multiple active paths
         to access the LUN."
    ::= 13830

    ocumEvtLunSingleActivePath    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The event indicates that there is only one active path
         to access the LUN."
    ::= 13831

    ocumEvtLunReachable    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The LUN is accessible."
    ::= 13840

    ocumEvtLunNotReachable    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The LUN is not accessible."
    ::= 13841

    ocumEvtLunOptimizedPathActive    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "There are optimized paths to access the LUN."
    ::= 13850

    ocumEvtLunOptimizedPathInactive    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "There are no optimized paths to access the LUN."
    ::= 13851

    ocumEvtLunHaPartnerPathActive    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "There are paths to access the LUN from HA partner node."
    ::= 138512

    ocumEvtLunHaPartnerPathInActive    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "There are no paths to access the LUN from HA partner node."
    ::= 138513

    -- alert related events

    ocumEvtAlertCreated    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "An alert has been created."
    ::= 13900

    ocumEvtAlertDeleted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "An alert has been deleted."
    ::= 13910

    ocumEvtAlertModified    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "An alert has been modified."
    ::= 13920

    -- qtree events

    ocumEvtQtreeFilesOk    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The qtree files count monitored by OnCommand Unified Manager server has
        not breached soft limit."
    ::= 14100

    ocumEvtQtreeFilesSoftLimitBreached    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The qtree files count monitored by OnCommand Unified Manager server has breached
         the soft limit."
    ::= 14101

    ocumEvtQtreeFilesHardLimitReached    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The qtree files count monitored by OnCommand Unified Manager server
         has reached the hard limit."
    ::= 14102

    ocumEvtQtreeSpaceOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The qtree monitored by OnCommand Unified Manager server has not breached
          soft limit."
    ::= 14110

    ocumEvtQtreeSpaceSoftLimitBreached    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The qtree monitored by OnCommand Unified Manager server has breached
         soft limit."
    ::= 14111

    ocumEvtQtreeSpaceHardLimitReached    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The qtree monitored by OnCommand Unified Manager server
         has reached hard limit."
    ::= 14112

    ocumEvtQtreeSpaceFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization by a qtree
         being managed by OnCommand Unified Manager server has crossed
         'full' threshold.
         Variable ocumEventSourceResourceKey identifies the qtree."
    ::= 14120

    ocumEvtQtreeSpaceNearlyFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization by a qtree
         being managed by OnCommand Unified Manager server has crossed
         'nearlyFull' threshold.
         Variable ocumEventSourceResourceKey identifies the qtree."
    ::= 14121

    ocumEvtQtreeSpaceThresholdOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization on the Qtree being
         managed by OnCommand Unified Manager server is below its
         'nearlyFull' threshold. Variable
         ocumEventSourceResourceKey identifies the qtree."
    ::= 14122

    -- snapshot policy events

    ocumEvtSnapshotPolicyEnabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshot Policy enabled."
    ::= 14200

    ocumEvtSnapshotPolicyDisabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshot Policy disabled."
    ::= 14201

    ocumEvtSnapshotPolicyCreated    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshot Policy created."
    ::= 14202

    ocumEvtSnapshotPolicyDeleted    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshot Policy deleted."
    ::= 14210

    ocumEvtSnapshotPolicyScheduleAdded    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshot Policy Schedule added."
    ::= 14220

    ocumEvtSnapshotPolicyScheduleModified    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshot Policy Schedule modified."
    ::= 14221

    ocumEvtSnapshotPolicyScheduleRemoved    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshot Policy Schedule removed."
    ::= 14222

    -- storage service events

    ocumEvtStorageServiceCreated    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage service created."
    ::= 14300

    ocumEvtStorageServiceSubscribed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The object was subscribed to a storage service."
    ::= 14310

    ocumEvtStorageServiceUnsubscribed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The object was unsubscribed from a storage service."
    ::= 14320

    ocumEvtStorageServiceUnexpectedRelationshipDeletion    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A managed SnapMirror Relationship was deleted out of band."
    ::= 14330

    ocumEvtStorageServiceUnexpectedVolumeDeletion    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A storage service member volume was deleted out of band."
    ::= 14340

    -- storage shelf events

    ocumEvtShelfFanNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage shelf fans are operational."
    ::= 14400

    ocumEvtShelfFanFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "One or more fans failed in storage shelf."
    ::= 14401

    ocumEvtShelfPowerSupplyNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage shelf power supplies are operational."
    ::= 14410

    ocumEvtShelfPowerSupplyFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "One or more power supplies failed in storage shelf."
    ::= 14411

    ocumEvtShelfVoltageNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage shelf voltage is normal."
    ::= 14420

    ocumEvtShelfVoltageAbnormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "One or more voltage sensors report abnormal voltage range in storage shelf."
    ::= 14421

    ocumEvtShelfCurrentNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage shelf voltage is normal."
    ::= 14430

    ocumEvtShelfCurrentAbnormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "One or more voltage sensors report abnormal current range in storage shelf."
    ::= 14431

    ocumEvtShelfTemperatureNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage shelf temperature is normal."
    ::= 14440

    ocumEvtShelfTemperatureAbnormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "One or more temperature sensors report abnormal temperature in storage shelf."
    ::= 14441

    ocumEvtStorageShelfDiscovered    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A Storage Shelf is discovered"
    ::= 14450

    ocumEvtStorageShelfRemoved    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A Storage Shelf is removed"
    ::= 14460

    -- protection job events

    ocumEvtProtectionJobTaskFailed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "One or more tasks have failed within a protection job."
    ::= 14600

    ocumEvtProtectionJobAborted    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A protection job was aborted."
    ::= 14610

    -- volume events

    -- volume availability events

    ocumEvtVolumeOnline    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume is online.
         Variable ocumEventSourceResourceKey identifies the volume."
    ::= 14700

    ocumEvtVolumeRestricted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume has been restricted.
         Variable ocumEventSourceResourceKey identifies the volume."
    ::= 14701

    ocumEvtVolumeOffline    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume is offline.
         Variable ocumEventSourceResourceKey identifies the volume."
    ::= 14702

    ocumEvtVolumeMixed    TRAP-TYPE
	ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"The volume is partially available."
    ::= 14703

    ocumEvtVolumeSpaceOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization on the volume being
         managed by OnCommand Unified Manager server is below its
         'nearlyFull' threshold. Variable
         ocumEventSourceResourceKey identifies the volume."
    ::= 14710

    ocumEvtVolumeNearlyFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization by a volume
         being managed by OnCommand Unified Manager server has crossed
         'nearlyFull' threshold.
         Variable ocumEventSourceResourceKey identifies the volume."
    ::= 14711

    ocumEvtVolumeFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization by a volume
         being managed by OnCommand Unified Manager server has crossed
         'full' threshold.
         Variable ocumEventSourceResourceKey identifies the volume."
    ::= 14712

    -- inodes events

    ocumEvtInodesUtilOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The number of inodes used up on volume
         managed by OnCommand Unified Manager server, is below
         the 'almostFull' threshold.
         Variable ocumEventSourceResourceKey identifies the volume."
    ::= 14720

    ocumEvtInodesAlmostFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The number of inodes used up on volume
         managed by OnCommand Unified Manager server, has exceeded
         the 'almostFull' threshold.
         Variable ocumEventSourceResourceKey identifies the volume."
    ::= 14721

    ocumEvtInodesFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The number of inodes used up on volume
         managed by OnCommand Unified Manager server, has exceeded
         the 'full' threshold.
         Variable ocumEventSourceResourceKey identifies the volume."
    ::= 14722

    -- Volume clone events

    ocumEvtVolumeCloneDiscovered    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A new volume clone has been discovered by OnCommand Unified Manager server."
    ::= 14730

    ocumEvtVolumeCloneDeleted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A volume clone that OnCommand Unified Manager server has been managing is no
        longer present."
    ::= 14740

    ocumEvtVolumeCloneSplit    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A volume clone has been split."
    ::= 14750

    -- Volume Overcommit events

    ocumEvtVolumeQtreeQuotaOvercommitOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume being managed by OnCommand Unified Manager server
         is below its 'almostOvercommitted' threshold. Variable
         ocumEventSourceResourceKey identifies the volume."
    ::= 14760

    ocumEvtVolumeQtreeQuotaAlmostOvercommitted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume being managed by OnCommand Unified Manager server
         has crossed the 'almostOvercommitted' threshold.
         Variable ocumEventSourceResourceKey identifies the volume."
    ::= 14761

    ocumEvtVolumeQtreeQuotaOvercommitted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume being managed by OnCommand Unified Manager server
         has crossed the 'overcommitted' threshold.
         Variable ocumEventSourceResourceKey identifies the volume."
    ::= 14762

    -- volume space reserve events

    ocumEvtVolumeInlineCompressionEnabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Inline Compression Enabled."
    ::= 14780

    ocumEvtVolumeInlineCompressionDisabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Inline Compression Disabled."
    ::= 14781

    ocumEvtVolumeBackgroundCompressionEnabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Background Compression Enabled."
    ::= 14790

    ocumEvtVolumeBackgroundCompressionDisabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Background Compression Disabled."
    ::= 14791

    ocumEvtVolumeDedupeEnabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Dedupe Enabled."
    ::= 14800

    ocumEvtVolumeDedupeDisabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Dedupe Disabled."
    ::= 14801

    ocumEvtVolumeEfficiencyOperationOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Efficiency Operation functioning normally."
    ::= 14810

    ocumEvtVolumeEfficiencyOperationError    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Efficiency Operation Error occurred."
    ::= 14811

    ocumEvtVolumeGrowthRateOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The Volume Growth Rate is Normal."
    ::= 14820

    ocumEvtVolumeGrowthRateAbnormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The Volume Growth Rate is Abnormal."
    ::= 14821

    ocumEvtVolumeRenamed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume was renamed."
    ::= 14830

    ocumEvtVolumeDiscovered    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume was discovered on a cluster."
    ::= 14840

    ocumEvtVolumeRemoved    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A volume is removed"
    ::= 14850

    ocumEvtVolumeMounted    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume was mounted."
    ::= 14860

    ocumEvtVolumeUnmounted    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume was unmounted."
    ::= 14861

    ocumEvtVolumeRemounted    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume was remounted."
    ::= 14862

    ocumEvtVolumeExportPolicyModified    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume is associated with a different export policy."
    ::= 14870

    ocumEvtVolumeDaysUntilFullNotSoon    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume will not be full soon."
    ::= 14880

    ocumEvtVolumeDaysUntilFullSoon    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume will be full soon."
    ::= 14881

    ocumEvtVolumeFractionalReserveModified    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume fractional reserve was modified."
    ::= 14890

    ocumEvtVolumeSpaceGuaranteeModified    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume space guarantee was modified."
    ::= 14900

    ocumEvtVolumeSpaceGuaranteeEnabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume space guarantee was enabled."
    ::= 14901

    ocumEvtVolumeSpaceGuaranteeDisabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume space guarantee was disabled."
    ::= 14902

    ocumEvtVolumeAutosizeEnabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Autosize enabled."
    ::= 14910

    ocumEvtVolumeAutosizeDisabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Autosize disabled."
    ::= 14911

    ocumEvtVolumeAutosizeModifiedMax    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Autosize maximum size modified."
    ::= 14912

    ocumEvtVolumeAutosizeModifiedIncrement    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Autosize increment size modified."
    ::= 14913

    ocumEvtVolumeMoveFinished    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume move is finished."
    ::= 14920

    ocumEvtVolumeMoveProgress    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume move in progress."
    ::= 14921

    ocumEvtVolumeMoveCompleted    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume move completed successfully."
    ::= 14922

    ocumEvtVolumeMoveCutoverDeferred    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Cutover was deferred."
    ::= 14923

    ocumEvtVolumeMoveFailed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume move failed."
    ::= 14924

    ocumEvtVolumeJunctionPathActive    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Junction Path Active."
    ::= 14930

    ocumEvtVolumeJunctionPathInactive    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Volume Junction Path Inactive."
    ::= 14931

    -- snapshot events

    ocumEvtSnapshotSpaceOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization by a snapshot being
         managed by OnCommand Unified Manager server is below its 'full' threshold.
         Variable ocumEventSourceResourceKey identifies the volume."
    ::= 15000

    ocumEvtSnapshotFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization by a snapshot being managed by
         OnCommand Unified Manager server has crossed 'full' threshold.
         Variable ocumEventSourceResourceKey identifies the volume."
    ::= 15001

    ocumEvtSnapshotTooMany    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Too many snapshots."
    ::= 15010

    ocumEvtSnapshotNotTooMany    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Not Too many snapshots."
    ::= 15011

    -- Snapshot Schedule Events

    ocumEvtSnapSchedModified    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The snapshot schedule has been modified on the
        storage system."
    ::= 15020

    ocumEvtSnapEnabled    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshots Enabled."
    ::= 15030

    ocumEvtSnapDisabled    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshots Disabled."
    ::= 15031

    ocumEvtSnapshotAutodeleteEnabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshot autodelete enabled."
    ::= 15040

    ocumEvtSnapshotAutodeleteDisabled    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshot autodelete disabled."
    ::= 15041

    ocumEvtSnapshotAutodeleteModified    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapshot autodelete configuration modified"
    ::= 15042

    ocumEvtVolumeSnapshotReserveDaysUntilFullNotSoon    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The snapshot reserve for the volume will not be full soon."
    ::= 15050

    ocumEvtVolumeSnapshotReserveDaysUntilFullSoon    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The snapshot reserve for the volume will be full in a few days."
    ::= 15051

    ocumEvtVolumeSnapshotReserveModified    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The volume snapshot reserve was modified."
    ::= 15060

    ocumEvtVolumeNextSnapshotPossible    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The next snapshot can be taken on the volume."
    ::= 15070

    ocumEvtVolumeNextSnapshotNotPossible    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The next snapshot cannot be taken on the volume due to lack of
        space."
    ::= 15071

    -- snapmirror events

    ocumEvtSnapmirrorRelationshipDiscovered    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A new SnapMirror Relationship was discovered."
    ::= 15200

    ocumEvtSnapmirrorRelationshipModified    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A SnapMirror Relationship was modified."
    ::= 15201

    ocumEvtSnapmirrorRelationshipDeleted    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A SnapMirror Relationship was deleted."
    ::= 15210

    ocumEvtSnapmirrorRelationshipHealthy    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
         "A SnapMirror Relationship is healthy."
    ::= 15220

    ocumEvtSnapmirrorRelationshipUnhealthy    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A SnapMirror Relationship is unhealthy."
    ::= 15221

     ocumEvtSnapmirrorRelationshipStateOk    TRAP-TYPE
     ENTERPRISE    netappOnCommandUnifiedManager
     VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
              }
      DESCRIPTION
          "The state of a SnapMirror Relationship state is ok."
    ::= 15230

    ocumEvtSnapmirrorRelationshipStateBrokenoff    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The state of a SnapMirror Relationship is broken-off."
    ::= 15231

    ocumEvtSnapmirrorRelationshipInitializeOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
             }
     DESCRIPTION
         "SnapMirror relationship initialize is ok."
    ::= 15240

    ocumEvtSnapmirrorRelationshipInitializeFailed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "SnapMirror relationship initialize failed."
    ::= 15241

    ocumEvtSnapmirrorRelationshipUpdateOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
               }
       DESCRIPTION
           "SnapMirror relationship update is ok."
    ::= 15250

    ocumEvtSnapmirrorRelationshipUpdateFailed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "SnapMirror relationship update failed."
    ::= 15251

    ocumEvtSnapmirrorRelationshipResyncOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
             }
     DESCRIPTION
         "SnapMirror relationship resync is ok."
    ::= 15252

    ocumEvtSnapmirrorRelationshipResyncFailed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "SnapMirror relationship resync failed."
    ::= 15253

    ocumEvtSnapMirrorRelationshipLagWarning TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapmirror Relationship Lag warning."
    ::= 15260

    ocumEvtSnapMirrorRelationshipLagError   TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapmirror Relationship Lag error."
    ::= 15261

    ocumEvtSnapMirrorRelationshipLagNormal   TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Snapmirror Relationship Lag normal."
    ::= 15262


    -- snapvault events

    ocumEvtSnapvaultRelationshipHealthy    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A SnapVault Relationship is healthy."
    ::= 15300

    ocumEvtSnapvaultRelationshipUnhealthy    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A SnapVault Relationship is unhealthy."
    ::= 15301

    ocumEvtSnapvaultRelationshipStateOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The state of a SnapVault Relationship state is ok."
    ::= 15310

    ocumEvtSnapvaultRelationshipStateBrokenoff    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The state of a SnapVault Relationship is broken-off."
    ::= 15311

    ocumEvtSnapvaultRelationshipInitializeOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
               }
       DESCRIPTION
           "SnapVault relationship initialize is ok."
    ::= 15320

    ocumEvtSnapvaultRelationshipInitializeFailed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "SnapVault relationship initialize failed."
    ::= 15321

    ocumEvtSnapvaultRelationshipUpdateOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
               }
       DESCRIPTION
           "SnapVault relationship update is ok."
    ::= 15330

    ocumEvtSnapvaultRelationshipUpdateFailed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "SnapVault relationship update failed."
    ::= 15331

    ocumEvtSnapvaultRelationshipResyncOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
               }
       DESCRIPTION
           "SnapVault relationship resync is ok."
    ::= 15332

    ocumEvtSnapvaultRelationshipResyncFailed    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "SnapVault relationship resync failed."
    ::= 15333

    ocumEvtSnapVaultRelationshipLagWarning TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "SnapVault Relationship Lag warning."
    ::= 15340

    ocumEvtSnapVaultRelationshipLagError   TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "SnapVault Relationship Lag error."
    ::= 15341

    ocumEvtSnapVaultRelationshipLagNormal   TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "SnapVault Relationship Lag normal."
    ::= 15342

    -- vserver events

    ocumEvtVserverCifsServiceStatusUp    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The CIFS protocol service is up on the Virtual Server."
    ::= 15400

    ocumEvtVserverCifsServiceStatusDown    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The CIFS protocol service is down on the Virtual Server."
    ::= 15401

    ocumEvtVserverFcServiceStatusUp    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The FC service is up on the Virtual Server."
    ::= 15410

    ocumEvtVserverFcServiceStatusDown    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The FC service is down on the Virtual Server."
    ::= 15411

    ocumEvtVserverIscsiServiceStatusUp    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The iSCSI protocol service is up on the Virtual Server."
    ::= 15420

    ocumEvtVserverIscsiServiceStatusDown    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The iSCSI protocol service is down on the Virtual Server."
    ::= 15421

    ocumEvtVserverNfsServiceStatusUp    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The NFS protocol service is up on the Virtual Server."
    ::= 15430

    ocumEvtVserverNfsServiceStatusDown    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The NFS protocol service is down on the Virtual Server."
    ::= 15431

    ocumEvtVserverCifsServiceNotConfigured    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The CIFS protocol service is not configured on the Virtual Server."
    ::= 15440

    ocumEvtVserverFcServiceNotConfigured    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The FC service is not configured on the Virtual Server."
    ::= 15450

    ocumEvtVserverIscsiServiceNotConfigured    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The iSCSI protocol service is not configured on the Virtual Server."
    ::= 15460

    ocumEvtVserverNfsServiceNotConfigured    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The NFS protocol service is not configured on the Virtual Server."
    ::= 15470

    ocumEvtVserverRenamed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A Virtual Server was renamed on a cluster."
    ::= 15480

    ocumEvtVserverUp    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
    }
    DESCRIPTION
        "A Virtual Server is up in a cluster."
    ::= 15490

    ocumEvtVserverDown    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
    }
    DESCRIPTION
          "A Virtual Server is down in a cluster."
    ::= 15491

    ocumEvtVserverDiscovered    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A Virtual Server was discovered on a cluster."
    ::= 15500

    ocumEvtVserverDeleted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A Virtual Server was deleted on a cluster."
    ::= 15510

    -- Vserver Storage Availability Events

    ocumEvtVserverStorageAvailable    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage for a Vserver is Available. Variable ocumEventSourceResourceKey identifies
        the Vserver"
    ::= 15520

    ocumEvtVserverStoragePartiallyAvailable    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage for a Vserver is Partially Available. Variable ocumEventSourceResourceKey
        identifies the Vserver"
    ::= 15521

    ocumEvtVserverStorageNotAvailable    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage for the Vserver is Not Available. Variable ocumEventSourceResourceKey
        identifies the Vserver"
    ::= 15522

    ocumEvtVserverSpaceOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The data space utilization on the infinteVol being
         managed by OnCommand Unified Manager server is below its
         'nearlyFull' threshold. Variable
         ocumEventSourceResourceKey identifies the Vserver for the
         corresponding infiniteVol."
    ::= 15530

    ocumEvtVserverNearlyFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The data space utilization by an infiniteVol
         being managed by OnCommand Unified Manager server has crossed
         'nearlyFull' threshold.
         Variable ocumEventSourceResourceKey identifies the Vserver for
         the corresponding infiniteVol."
    ::= 15531

    ocumEvtVserverFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The data space utilization by an infiniteVol
         being managed by OnCommand Unified Manager server has crossed
         'full' threshold.
         Variable ocumEventSourceResourceKey identifies the Vserver for the
         corresponding infiniteVol."
    ::= 15532

    -- vserver snapshot events

    ocumEvtVserverSnapshotUsageOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The snapshot space utilization on the
         vserver is below its usage threshold.
         Variable ocumEventSourceResourceKey identifies the storage class."
    ::= 15540

    ocumEvtVserverSnapshotUsageExceeded    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The snapshot space utilization on the
         vserver has exceeded its usage threshold.
         Variable ocumEventSourceResourceKey identifies the storage class."
    ::= 15541

    -- vserver namespace mirror availability events

    ocumEvtVserverNsMirrorAvailabilityOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Namespace mirror constituents are Available. Variable ocumEventSourceResourceKey
        identifies the Vserver"
    ::= 15550

    ocumEvtVserverNsMirrorAvailabilityHavingIssues    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Namespace mirror constituents are having Availability Issues. Variable ocumEventSourceResourceKey
        identifies the Vserver"
    ::= 15551

    ocumEvtVserverNamespaceSpaceOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The data space utilization on the namespace constituent of
         an infinteVol being managed by OnCommand Unified Manager server
         is below its 'nearlyFull' threshold. Variable
         ocumEventSourceResourceKey identifies the Vserver for the
         corresponding infiniteVol."
    ::= 15560

    ocumEvtVserverNamespaceNearlyFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The data space utilization by a namespace constituent of
         an infiniteVol being managed by OnCommand Unified Manager
         server has crossed 'nearlyFull' threshold.
         Variable ocumEventSourceResourceKey identifies the Vserver for
         the corresponding infiniteVol."
    ::= 15561

    ocumEvtVserverNamespaceFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The data space utilization by a namespace constituent of
         an infiniteVol being managed by OnCommand Unified Manager
         server has crossed 'full' threshold.
         Variable ocumEventSourceResourceKey identifies the Vserver for the
         corresponding infiniteVol."
    ::= 15562

    -- vserver storage class events

    ocumEvtVserverStorageClassAvailable    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A Vserver Storage Class is Available. Variable ocumEventSourceResourceKey
        identifies the Storage Class"
    ::= 15600

    ocumEvtVserverStorageClassPartiallyAvailable    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A Vserver Storage Class is Partially Available. Variable ocumEventSourceResourceKey
        identifies the Storage Class"
    ::= 15601

    ocumEvtVserverStorageClassNotAvailable    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "A Vserver Storage Class is Not Available. Variable ocumEventSourceResourceKey
        identifies the Storage Class"
    ::= 15602

    ocumEvtVserverStorageClassSpaceOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization on the Vserver storage class of an
         infinite Volume being managed by OnCommand Unified Manager
         server is below its 'nearlyFull' threshold. Variable
         ocumEventSourceResourceKey identifies the Storage Class."
    ::= 15610

    ocumEvtVserverStorageClassNearlyFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization by a Vserver storage class of an infinite
         volume being managed by OnCommand Unified Manager server has crossed
         'nearlyFull' threshold.
         Variable ocumEventSourceResourceKey identifies the storage class."
    ::= 15611

    ocumEvtVserverStorageClassFull    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The space utilization by a Vserver storage class of an infinite
         volume being managed by OnCommand Unified Manager server has
         crossed 'full' threshold.
         Variable ocumEventSourceResourceKey identifies the storage class."
    ::= 15612

    ocumEvtVserverStorageClassSnapshotUsageOk    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The snapshot space utilization on the storage class of
         Vserver is below its usage threshold.
         Variable ocumEventSourceResourceKey identifies the storage class."
    ::= 15620

    ocumEvtVserverStorageClassSnapshotUsageExceeded    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The snapshot space utilization on the storage class of
         Vserver has exceeded its usage threshold.
         Variable ocumEventSourceResourceKey identifies the storage class."
    ::= 15621

    -- script events

    ocumEvtScriptNormal    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "A normal event generated by a script."
    ::= 15700

    ocumEvtScriptInformation    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "An information event generated by a script."
    ::= 15701

    ocumEvtScriptWarning    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "A warning event generated by a script."
    ::= 15702

    ocumEvtScriptError    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "An error event generated by a script."
    ::= 15703

    ocumEvtScriptCritical    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "A critical event generated by a script."
    ::= 15704

    -- user or group quota traps

    ocumEvtUserOrGroupQuotaFileCountOk    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The user or group quota file count monitored by OnCommand Unified Manager server has
         not breached the soft limit."
    ::= 15800

    ocumEvtUserOrGroupQuotaFileCountSoftLimitBreached    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The user or group quota files count monitored by OnCommand Unified Manager server has
         breached the soft limit."
    ::= 15801

    ocumEvtUserOrGroupQuotaFileCountHardLimitReached    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The user or group quota file count monitored by OnCommand Unified Manager server has
         reached the hard limit."
    ::= 15802

    ocumEvtUserOrGroupQuotaDiskSpaceOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The user or group quota disk space monitored by OnCommand Unified Manager server has
         not breached the soft limit."
    ::= 15810

    ocumEvtUserOrGroupQuotaDiskSpaceSoftLimitBreached    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The user or group quota disk space monitored by OnCommand Unified Manager server has
         breached the soft limit."
    ::= 15811

    ocumEvtUserOrGroupQuotaDiskSpaceHardLimitReached    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The user or group quota disk space space monitored by OnCommand Unified Manager server has
         reached the hard limit."
    ::= 15812

    ocumPerformanceIncident    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "A performance incident event was generated."
    ::= 15820

    ocumPerformanceIncidentCleared    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "A performance incident is cleared."
    ::= 15821

    ocumPerformanceError    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "A performance error event was generated."
    ::= 15822

    ocumPerformanceWarning    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "A performance warning event was generated."
    ::= 15823

    ocumPerformanceInformation    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "A performance information event was generated."
    ::= 15824

-- volume thin-provision space events

    ocumThinProvisionVolumeSpaceAtRisk    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "A space risk for thin-provision volume is raised"
    ::= 15830

    ocumThinProvisionVolumeSpaceNotAtRisk    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "A space not at risk for thin-provision volume is raised"
    ::= 15831

    ocumDiskShelfConnectivityInMultiPath    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Disk Shelf has multipath connectivity"
    ::= 15840

    ocumDiskShelfConnectivityNotInMultiPath    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Disk Shelf is at Risk as it does not have multipath connectivity"
    ::= 15841

    ocumDiskShelfConnectivityPathNormal   TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Disk Shelf has normal connectivity"
    ::= 15850

    ocumDiskShelfConnectivityPathFailure    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Connectivity failure between two Disk Shelf "
    ::= 15851

    ocumClusterAddNeeded    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Cluster needs to be added to receive performance events."
    ::= 15860

    ocumClusterAdded    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Cluster added to receive performance events."
    ::= 15861

    -- traps for MCC link issues

    ocumEvtMccNodeSwitchFcviLinksUp    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All FC-VI links between node and switch are up."
    ::= 15900

    ocumEvtMccNodeSwitchFcviLinksOneOrMoreDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "One or more FC-VI links between node and switch are down."
    ::= 15901

    ocumEvtMccNodeSwitchFcviLinksDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All FC-VI links between node and switch are down."
    ::= 15902

    ocumEvtMccNodeSwitchFcLinksUp    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All FC links between node and switch are up."
    ::= 15910

    ocumEvtMccNodeSwitchFcLinksOneOrMoreDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "One or more FC links between node and switch are down."
    ::= 15911

    ocumEvtMccNodeSwitchFcLinksDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All FC links between node and switch are down."
    ::= 15912

    ocumEvtMccSwitchBridgeFcLinksUp    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All FC links between switch and bridge are up."
    ::= 15920

    ocumEvtMccSwitchBridgeFcLinksDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All FC links between switch and bridge are down."
    ::= 15921

    -- traps for MCC switch component failure related issues

    ocumEvtSwitchTemperatureNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage switch temperature is normal."
    ::= 16000

    ocumEvtSwitchTemperatureAbnormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Abnormal temperature in storage switch."
    ::= 16001


    ocumEvtSwitchFansNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The fans on the storage switch are functioning normally."
    ::= 16010

    ocumEvtSwitchFansOneOrMoreFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "One or more fans have failed on the storage switch."
    ::= 16011

    ocumEvtSwitchPowerSuppliesNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The power supplies on the storage switch are functioning normally."
    ::= 16020

    ocumEvtSwitchPowerSuppliesOneOrMoreFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "One or more power supplies have failed on the storage switch."
    ::= 16021

    ocumEvtSwitchReachable    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Switch is reachable."
    ::= 16030

    ocumEvtSwitchUnreachable    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Switch is unreachable."
    ::= 16031

    ocumEvtSwitchTemperatureSensorNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Storage switch temperature sensors are normal."
    ::= 16040

    ocumEvtSwitchTemperatureSensorFailed    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "One or more temperature sensors in the storage switch have failed."
    ::= 16041

    -- trap for MCC bridge related issues

    ocumEvtBridgeTemperatureNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Bridge temperature is normal."
    ::= 16100

    ocumEvtBridgeTemperatureAbnormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Abnormal temperature in the bridge."
    ::= 16101

    ocumEvtBridgeReachable    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Bridge is reachable."
    ::= 16110

    ocumEvtBridgeUnreachable    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Bridge is unreachable."
    ::= 16111

    -- traps for mcc inter cluster related issues

    ocumEvtMetroClusterAllLinksBetweenPartnersUp    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "All Links between the clusters in MCC environment are Up."
    ::= 16200

    ocumEvtMetroClusterAllLinksBetweenPartnersDown    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "MetroCluster partner cluster is not reachable."
    ::= 16201

    ocumEvtMetroClusterPartnersReachableOverPeeringNetwork    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "IP link is up between the clusters in MCC environment."
    ::= 16210

    ocumEvtMetroClusterPartnersNotReachableOverPeeringNetwork    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "MetroCluster partner cluster is not reachable over peering network."
    ::= 16211

	ocumEvtMetroClusterAllISLBetweenSwitchesUp    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "All links between the switches are up."
    ::= 16220

    ocumEvtMetroClusterAllISLBetweenSwitchesDown    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "All links between the switches are down."
    ::= 16221

	ocumEvtMetroClusterDRStatusOk    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Metrocluster switched over successfully."
    ::= 16230

    ocumEvtMetroClusterDRStatusPartiallyImpacted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Metrocluster configuration is partically switched over."
    ::= 16231

ocumEvtMetroClusterDRStatusImpacted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Metrocluster disaster recovery capability is impacted."
    ::= 16232

	ocumEvtMetroClusterDRStatusCompleted    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Metrocluster disaster recovery capability is Normal"
    ::= 16233

	ocumEvtMetroClusterAggregateMirrorNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "MetroCluster aggregate mirroring is normal."
    ::= 16300

	ocumEvtMetroClusterAggregateMirrorDegraded    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "MetroCluster aggregate mirroring is in a degraded state."
    ::= 16301

	ocumEvtNoSpareDiskLeftBehind    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "No spare disk is left behind during MetroCluster switchback operation."
    ::= 16310

	ocumEvtSpareDiskLeftBehind    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "Spare disk is left behind during MetroCluster switchback operation."
    ::= 16311

    ocumEvtMccBridgeStorageStackSASLinksUp    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "All SAS links between bridge and storage stack are up"
    ::= 16320

	ocumEvtMccBridgeStorageStackSASLinksDown    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "All SAS links between bridge and storage stack are down"
    ::= 16321

    ocumEvtClusterFlashDiskFewerSpareBlockNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The flash disks monitored by the OnCommand Unified Manager server are operational."
    ::= 16330

    ocumEvtClusterFlashDiskFewerSpareBlockError    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The flash disks monitored by the OnCommand Unified Manager server have
         consumed some of the internal spare blocks."
    ::= 16331

    ocumEvtClusterFlashDiskNoSpareBlockNormal    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The flash disks monitored by the OnCommand Unified Manager server are operational."
    ::= 16340

    ocumEvtClusterFlashDiskNoSpareBlockCritical    TRAP-TYPE
    ENTERPRISE    netappOnCommandUnifiedManager
    VARIABLES    {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "The flash disks monitored by the OnCommand Unified Manager server have
         almost consumed the internal spare blocks."
    ::= 16341

	-- traps for Backup Creation Issues

    ocumEvtBackupCreationSucceeded    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
            "Backup creation job has succeeded."
    ::= 16350

    ocumEvtBackupCreationFailed    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
            "Backup creation job has failed."
    ::= 16351

    ocumEvtBackupCreationNormal TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
            "Backup creation job is normal."
    ::= 16352


    ocumEvtClusterUnsupportedDisksNone    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "No unsupported disk are discovered."
    ::= 13360

    ocumEvtClusterUnsupportedDisksSome    TRAP-TYPE
    ENTERPRISE    netappOnCommandUnifiedManager
    VARIABLES   {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
            }
    DESCRIPTION
        "some unsupported disks are discovered."
    ::= 13361

    ocumEvtMccInterNodeLinksUp    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All links between the metrocluster nodes are up."
    ::= 16400

    ocumEvtMccInterNodeLinksOneOrMoreDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "One or more links between the metrocluster nodes are down."
    ::= 16401

    ocumEvtMccInterNodeLinksDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All links between the metrocluster nodes are down."
    ::= 16402

    ocumEvtMccNodeBridgeLinksUp    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All links between the node and bridge are up."
    ::= 16410

    ocumEvtMccNodeBridgeLinksDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All links between the node and bridge are down."
    ::= 16411


    ocumEvtMccNodeStackLinksUp    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All SAS links between the Metrocluster node and storage stack are up."
    ::= 16420

    ocumEvtMccNodeStackLinksOneOrMoreDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "One or more SAS links between the Metrocluster node and storage stack are down."
    ::= 16421

    ocumEvtMccNodeStackLinksDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "All SAS links between the Metrocluster node and storage stack are down."
    ::= 16422

    ocumEvtMccAutomaticUnplannedSwitchOverDisabled    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Automatic unplanned switch over disabled."
    ::= 16500

    ocumEvtMccAutomaticUnplannedSwitchOverEnabled    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Automatic unplanned switch over enabled."
    ::= 16501

	ocumEvtEMSWarningEventReceived    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Warning EMS Received."
    ::= 16600

    ocumEvtEMSCriticalEventReceived    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Critical EMS received."
    ::= 16610

    ocumEvtEMSErrorEventReceived    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Error EMS received."
    ::= 16620

    ocumEvtEMSInformationalEventReceived    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Informational EMS received."
    ::= 16630

    ocumEvtEMSNoticeEventReceived    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Notice EMS received."
    ::= 16640

    ocumEvtEMSDebugEventReceived    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Debug EMS received."
    ::= 16650

    ocumEvtEMSEmergencyEventReceived    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Emergency EMS received."
    ::= 16660

    ocumEvtEMSAlertEventReceived    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
            "Alert EMS received."
    ::= 16670

    ocumEvtHeartbeatServiceStatusDown    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"The Heartbeat service status is down due to error threshold exceed."
    ::= 16700

    ocumEvtHeartbeatServiceStatusUp    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"The Heartbeat service status is up."
    ::= 16701

    ocumEvtUnifiedManagerDiskSpaceNearlyFull    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"The Unified Manager database partition is above 90% capacity."
    ::= 16800

    ocumEvtUnifiedManagerDiskSpaceFull    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"The Unified Manager database partition is above 95% capacity."
    ::= 16801

    ocumEvtUnifiedManagerDiskSpaceNormal    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"Unified Manager database partition has Enough Disk Space."
    ::= 16802

    ocumEvtUnifiedManagerDataNormal    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"Unified Manager can collect and analyze performance data."
    ::= 16813

    ocumEvtUnifiedManagerDataMissingAnalyze    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"Unified Manager can’t analyze performance data."
    ::= 16814

    ocumEvtUnifiedManagerDataMissingCollection    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"Unified Manager can’t collect performance data."
    ::= 16815

    ocumAggregateLatencyIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with aggregate latency."
    ::= 16820

    ocumAggregateLatencyWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with aggregate latency."
    ::= 16821

    ocumAggregateLatencyCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An aggregate latency incident is cleared."
    ::= 16822

    ocumAggregateIopsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with aggregate IOPS."
    ::= 16830

    ocumAggregateIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with aggregate IOPS."
    ::= 16831

    ocumAggregateIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An aggregate IOPS incident is cleared."
    ::= 16832

    ocumAggregateMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with aggregate MBps."
    ::= 16840

    ocumAggregateMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with aggregate MBps."
    ::= 16841

    ocumAggregateMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An aggregate MBps incident is cleared."
    ::= 16842

    ocumAggregatePerfCapacityUsedIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with aggregate performance capacity used."
    ::= 16850

    ocumAggregatePerfCapacityUsedWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with aggregate performance capacity used."
    ::= 16851

    ocumAggregatePerfCapacityUsedCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An aggregate performance capacity used incident is cleared."
    ::= 16852

    ocumAggregateUtilizationIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with aggregate utilization."
    ::= 16860

    ocumAggregateUtilizationWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with aggregate utilization."
    ::= 16861

    ocumAggregateUtilizationCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An aggregate utilization incident is cleared."
    ::= 16862

    ocumNodeLatencyIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with node latency."
    ::= 16870

    ocumNodeLatencyWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with node latency."
    ::= 16871

    ocumNodeLatencyCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A node latency incident is cleared."
    ::= 16872

    ocumNodeIopsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with node IOPS."
    ::= 16880

    ocumNodeIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with node IOPS."
    ::= 16881

    ocumNodeIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A node IOPS incident is cleared."
    ::= 16882

    ocumNodeMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with node MBps."
    ::= 16890

    ocumNodeMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with node MBps."
    ::= 16891

    ocumNodeMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A node MBps incident is cleared."
    ::= 16892

    ocumNodePerfCapacityUsedIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with node performance capacity used."
    ::= 16900

    ocumNodePerfCapacityUsedWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with node performance capacity used."
    ::= 16901

    ocumNodePerfCapacityUsedCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A node performance capacity used incident is cleared."
    ::= 16902

    ocumNodePerfCapacityUsedTakeoverIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with node performance capacity used -takeover."
    ::= 16910

    ocumNodePerfCapacityUsedTakeoverWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with node performance capacity used -takeover"
    ::= 16911

    ocumNodePerfCapacityUsedTakeoverCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A node performance capacity used -takeover incident is cleared."
    ::= 16912

    ocumNodeUtilizationIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with node utilization."
    ::= 16920

    ocumNodeUtilizationWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with node utilization."
    ::= 16921

    ocumNodeUtilizationCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A node utilization incident is cleared."
    ::= 16922

    ocumClusterIopsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with cluster IOPS."
    ::= 16930

    ocumClusterIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with cluster IOPS."
    ::= 16931

    ocumClusterIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A cluster IOPS incident is cleared."
    ::= 16932

    ocumClusterMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with cluster MBps."
    ::= 16940

    ocumClusterMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with cluster MBps."
    ::= 16941

    ocumClusterMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A cluster MBps incident is cleared."
    ::= 16942

    ocumNetworkPortUtilizationIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with network port utilization."
    ::= 16950

    ocumNetworkPortUtilizationWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with network port utilization."
    ::= 16951

    ocumNetworkPortUtilizationCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A network port utilization incident is cleared."
    ::= 16952

    ocumNetworkPortMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with network port MBps."
    ::= 16960

    ocumNetworkPortMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with network port MBps."
    ::= 16961

    ocumNetworkPortMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A network port MBps incident is cleared."
    ::= 16962

    ocumSvmLatencyIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with svm latency."
    ::= 16970

    ocumSvmLatencyWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with SVM latency."
    ::= 16971

    ocumSvmLatencyCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A SVM latency incident is cleared."
    ::= 16972

    ocumSvmIopsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with SVM IOPS."
    ::= 16980

    ocumSvmIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with SVM IOPS."
    ::= 16981

    ocumSvmIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A SVM IOPS incident is cleared."
    ::= 16982

    ocumSvmMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with SVM MBps."
    ::= 16990

    ocumSvmMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with SVM MBps."
    ::= 16991

    ocumSvmMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A SVM MBps incident is cleared."
    ::= 16992

    ocumVolumeLatencyIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume latency."
    ::= 17000

    ocumVolumeLatencyWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume latency."
    ::= 17001

    ocumVolumeLatencyCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume latency incident is cleared."
    ::= 17002

    ocumVolumeIopsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume IOPS."
    ::= 17010

    ocumVolumeIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume IOPS."
    ::= 17011

    ocumVolumeIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume IOPS incident is cleared."
    ::= 17012

    ocumVolumeMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume MBps."
    ::= 17020

    ocumVolumeMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume MBps."
    ::= 17021

    ocumVolumeMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume MBps incident is cleared."
    ::= 17022

    ocumVolumeCacheMissRatioIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume cache miss ratio."
    ::= 17030

    ocumVolumeCacheMissRatioWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume cache miss ratio."
    ::= 17031

    ocumVolumeCacheMissRatioCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume cache miss ratio incident is cleared."
    ::= 17032

    ocumVolumeLatencyIopsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume latency and IOPS."
    ::= 17040

    ocumVolumeLatencyIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume latency and IOPS."
    ::= 17041

    ocumVolumeLatencyIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume latency and IOPS incident is cleared."
    ::= 17042

    ocumVolumeLatencyMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume latency and MBps."
    ::= 17050

    ocumVolumeLatencyMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume latency and MBps."
    ::= 17051

    ocumVolumeLatencyMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume latency and MBps incident is cleared."
    ::= 17052

    ocumVolumeLatencyAggregatePerfCapacityUsedIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume latency and aggregate performance capacity used."
    ::= 17060

    ocumVolumeLatencyAggregatePerfCapacityUsedWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume latency and aggregate performance capacity used."
    ::= 17061

    ocumVolumeLatencyAggregatePerfCapacityUsedCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume latency and aggregate performance capacity used incident is cleared."
    ::= 17062

    ocumVolumeLatencyAggregateUtilizationIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume latency and aggregate utilization."
    ::= 17070

    ocumVolumeLatencyAggregateUtilizationWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume latency and aggregate utilization."
    ::= 17071

    ocumVolumeLatencyAggregateUtilizationCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume latency and aggregate utilization incident is cleared."
    ::= 17072

    ocumVolumeLatencyNodePerfCapacityUsedIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume latency and node performance capacity used."
    ::= 17080

    ocumVolumeLatencyNodePerfCapacityUsedWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume latency and node performance capacity used."
    ::= 17081

    ocumVolumeLatencyNodePerfCapacityUsedCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume latency and node performance capacity used incident is cleared."
    ::= 17082

    ocumVolumeLatencyAggregatePerfCapacityUsedTakeoverIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume latency and node performance capacity used -takeover."
    ::= 17090

    ocumVolumeLatencyAggregatePerfCapacityUsedTakeoverWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume latency and node performance capacity used -takeover."
    ::= 17091

    ocumVolumeLatencyAggregatePerfCapacityUsedTakeoverCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume latency and node performance capacity used -takeover incident is cleared."
    ::= 17092

    ocumVolumeLatencyNodeUtilizationIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with volume latency and node utilization."
    ::= 17100

    ocumVolumeLatencyNodeUtilizationWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with volume latency and node utilization."
    ::= 17101

    ocumVolumeLatencyNodeUtilizationCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A volume latency and node utilization incident is cleared."
    ::= 17102

    ocumLunLatencyIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with LUN latency."
    ::= 17110

    ocumLunLatencyWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with LUN latency."
    ::= 17111

    ocumLunLatencyCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A LUN latency incident is cleared."
    ::= 17112

    ocumLunIopsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with LUN IOPS."
    ::= 17120

    ocumLunIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with LUN IOPS."
    ::= 17121

    ocumLunIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A LUN IOPS incident is cleared."
    ::= 17122

    ocumLunMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with LUN MBps."
    ::= 17130

    ocumLunMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with LUN MBps."
    ::= 17131

    ocumLunMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A LUN MBps incident is cleared."
    ::= 17132

    ocumLunLatencyIopsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with LUN latency and IOPS."
    ::= 17140

    ocumLunLatencyIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with LUN latency and IOPS."
    ::= 17141

    ocumLunLatencyIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A LUN latency and IOPS incident is cleared."
    ::= 17142

    ocumLunLatencyMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with LUN latency and MBps."
    ::= 17150

    ocumLunLatencyMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with LUN latency and MBps."
    ::= 17151

    ocumLunLatencyMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A LUN latency and MBps incident is cleared."
    ::= 17152

    ocumLunLatencyAggregatePerfCapacityUsedIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with LUN latency and aggregate performance capacity used."
    ::= 17160

    ocumLunLatencyAggregatePerfCapacityUsedWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with LUN latency and aggregate performance capacity used."
    ::= 17161

    ocumLunLatencyAggregatePerfCapacityUsedCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A LUN latency and aggregate performance capacity used incident is cleared."
    ::= 17162

    ocumLunLatencyAggregateUtilizationIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with LUN latency and aggregate utilization."
    ::= 17170

    ocumLunLatencyAggregateUtilizationWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with LUN latency and aggregate utilization."
    ::= 17171

    ocumLunLatencyAggregateUtilizationCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A LUN latency and aggregate utilization incident is cleared."
    ::= 17172

    ocumLunLatencyNodePerfCapacityUsedIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with LUN latency and node performance capacity used."
    ::= 17180

    ocumLunLatencyNodePerfCapacityUsedWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with LUN latency and node performance capacity used."
    ::= 17181

    ocumLunLatencyNodePerfCapacityUsedCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A LUN latency and node performance capacity used incident is cleared."
    ::= 17182

    ocumLunLatencyAggregatePerfCapacityUsedTakeoverIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with LUN latency and node performance capacity used -takeover."
    ::= 17190

    ocumLunLatencyAggregatePerfCapacityUsedTakeoverWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with LUN latency and node performance capacity used -takeover."
    ::= 17191

    ocumLunLatencyAggregatePerfCapacityUsedTakeoverCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A LUN latency and node performance capacity used -takeover incident is cleared."
    ::= 17192

    ocumLunLatencyNodeUtilizationIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with LUN latency and node utilization."
    ::= 17200

    ocumLunLatencyNodeUtilizationWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with LUN latency and node utilization."
    ::= 17201

    ocumLunLatencyNodeUtilizationCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A LUN latency and node utilization incident is cleared."
    ::= 17202

    ocumNetworkLifMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with Network LIF MBps."
    ::= 17210

    ocumNetworkLifMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with Network LIF MBps."
    ::= 17211

    ocumNetworkLifMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A Network LIF MBps incident is cleared."
    ::= 17212

    ocumFcpPortUtilizationIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with FCP port utilization."
    ::= 17220

    ocumFcpPortUtilizationWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with FCP port utilization."
    ::= 17221

    ocumFcpPortUtilizationCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A FCP port utilization incident is cleared."
    ::= 17222

    ocumFcpPortMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with fcp port MBps."
    ::= 17230

    ocumFcpPortMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with FCP port MBps."
    ::= 17231

    ocumFcpPortMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A FCP port MBps incident is cleared."
    ::= 17232

    ocumAggregateDisksOverUtilizedWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with aggregate disks over-utilized."
    ::= 17240

    ocumAggregateDisksOverUtilizedCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A aggregate disks over-utilized warning is cleared."
    ::= 17241

    ocumNodeHaPairOverUtilizedInformation    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A information is notified with node HA pair over-utilized."
    ::= 17250

    ocumNodeHaPairOverUtilizedCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A node HA pair over-utilized warning is cleared."
    ::= 17251

    ocumNodeDiskFragmentationWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with node disk fragmentation."
    ::= 17260

    ocumNodeDiskFragmentationCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A node disk fragmentation warning is cleared."
    ::= 17261

    ocumNodeOverUtilizedWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with node over-utilized."
    ::= 17270

    ocumNodeOverUtilizedCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A node over-utilized warning is cleared."
    ::= 17271

    -- this type is no longer used, keep it here for the reference from the old migration step
    ocumClusterDynamicEventWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with cluster dynamic event."
    ::= 17280

    -- this type is no longer used, keep it here for the reference from the old migration step
    ocumClusterDynamicEventCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A cluster dynamic event warning is cleared."
    ::= 17281

    -- this type is no longer used, keep it here for the reference from the old migration step
    ocumNodeDynamicEventWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with node dynamic event."
    ::= 17290

    -- this type is no longer used, keep it here for the reference from the old migration step
    ocumNodeDynamicEventCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A node dynamic event warning is cleared."
    ::= 17291

    -- this type is no longer used, keep it here for the reference from the old migration step
    ocumAggregateDynamicEventWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with aggregate dynamic event."
    ::= 17300

    -- this type is no longer used, keep it here for the reference from the old migration step
    ocumAggregateDynamicEventCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A aggregate dynamic event warning is cleared."
    ::= 17301

    ocumFcpLifMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with FCP LIF MBps."
    ::= 17310

    ocumFcpLifMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with FCP LIF MBps."
    ::= 17311

    ocumFcpLifMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A FCP LIF MBps incident is cleared."
    ::= 17312

    ocumEvtClusterFabricpoolLicenseCapacityLimitExceeded    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
    "Cluster FabricPool license capacity has exceeded 'full' threshold limit."
    ::= 17321

    ocumEvtClusterFabricpoolLicenseCapacityLimitNormal    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
    "Cluster FabricPool license capacity is below 'full' threshold limit."
    ::= 17322

    ocumEventExternalCapacityUnreachable    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
    "The external capacity tier is not reachable for the composite aggregate."
    ::= 17331

    ocumEventExternalCapacityReachable    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                }
    DESCRIPTION
    "The external capacity tier is reachable for the composite aggregate."
    ::= 17332

    ocumEventExternalCapacityPartiallyReachable    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                }
    DESCRIPTION
    "The external capacity tier is partially reachable for the composite aggregate."
    ::= 17333

    ocumQosVolumeMaxIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with QoS volume max IOPS."
    ::= 17340

    ocumQosVolumeMaxIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A QoS volume max IOPS warning is cleared."
    ::= 17341

    ocumQosVolumeMaxMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with QoS volume max MBPS."
    ::= 17350

    ocumQosVolumeMaxMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A QoS volume max MBPS warning is cleared."
    ::= 17351


    ocumQosLunMaxIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with QoS lun max IOPS."
    ::= 17360

    ocumQosLunMaxIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A QoS lun max IOPS warning is cleared."
    ::= 17361


    ocumQosLunMaxMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with QoS lun max MBPS."
    ::= 17370

    ocumQosLunMaxMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A QoS lun max MBPS warning is cleared."
    ::= 17371


    ocumQosVolumeMaxIopsPerTbWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with QoS volume max IOPS/TB."
    ::= 17380

    ocumQosVolumeMaxIopsPerTbCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A QoS volume max IOPS/TB warning is cleared."
    ::= 17381

    -- this type is no longer used, keep it here for the reference from the old migration step
    ocumQosLunMaxIopsPerTbWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with QoS lun max IOPS/TB."
    ::= 17390

    -- this type is no longer used, keep it here for the reference from the old migration step
    ocumQosLunMaxIopsPerTbCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A QoS lun max IOPS/TB warning is cleared."
    ::= 17391

    ocumArlNetraCaCheckFailed    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An error occurs during the relocation of an aggregate, when the destination node cannot reach the object stores."
    ::= 17400

    ocumGbNetraCaCheckFailed    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Object store is unreachable for storage failover giveback."
    ::= 17410

    ocumObjstoreHostUnresolvable    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Object store host is unresolvable."
    ::= 17420

    ocumObjstoreInterClusterLifDown    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Operational LIF was Down to Connect with Object Store."
    ::= 17430

    ocumWaflCaLatencyThreashold    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Latency threshold breached between Aggregate and Object Store."
    ::= 17440

-- this type is no longer used, keep it here for the reference from the old migration step
    ocumS3BucketSignatureMismatch    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Signature mismatched communicating with S3 server."
    ::= 17450

    ocumCloudAwsMetadataConnFail    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Failed to connect between AWS IAM and AWS metadata server."
    ::= 17460

    ocumCloudAwsIamCredsExpired    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "AWS IAM credential expired."
    ::= 17470

    ocumCloudAwsIamCredsInvalid    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "AWS IAM credential was invalid."
    ::= 17471

    ocumCloudAwsIamCredsNotFound    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "AWS IAM credential was not found."
    ::= 17472

    ocumCloudAwsIamCredsNotInitialized    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "AWS IAM credential was not initialized."
    ::= 17473

    ocumCloudAwsIamRoleInvalid    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "AWS IAM role was invalid."
    ::= 17480

    ocumCloudAwsIamRoleNotFound    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "AWS IAM role was not found."
    ::= 17481

    ocumQosMonitorMemoryMaxed    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "QoS dynamic memory hits its limit for the current platform hardware."
    ::= 17490

    ocumQosMonitorMemoryAbated    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "QoS dynamic memory is no longer at its limit for the current platform hardware."
    ::= 17491

-- this type is no longer used, keep it here for the reference from the old migration step
    ocumQosViolationReport    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Hourly report provides a snapshot of violation detection status for the Quality of Service (QoS) policy groups."
    ::= 17500

    ocumEvtUnifiedManagerMemoryLow    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"The Unified Manager memory is running low"
    ::= 17510

    ocumEvtUnifiedManagerMemoryAlmostOut    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"The Unified Manager memory is running out."
    ::= 17511

    ocumEvtUnifiedManagerMemoryNormal    TRAP-TYPE
    ENTERPRISE    netappOnCommandUnifiedManager
    VARIABLES       {
                ocumSystemId,
                ocumEventName,
                ocumEventSeverity,
                ocumEventImpactLevel,
                ocumEventTimestamp,
                ocumEventMessage,
                ocumEventMessageDetails,
                ocumEventSourceResourceKey,
                ocumEventSourceFullName,
                ocumEventSourceType,
                ocumEventSourceHealthStatus,
                ocumEventSourceScopedResourceKey,
                ocumEventSourceScopedFullName,
                ocumEventSourceClusterResourceKey,
                ocumEventSourceClusterFullName,
                ocumEventState
                    }
    DESCRIPTION
	"Unified Manager memory is normal."
    ::= 17512

    ocumAlertTest    TRAP-TYPE
    ENTERPRISE    netappOnCommandUnifiedManager
    VARIABLES       {
                ocumSystemId,
                ocumTestAlertTimestamp
                    }
    DESCRIPTION
    "This is a Test Alert"
    ::= 11111

    nvmeNamespaceStatusOnline    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "NVMe Namespace Online."
    ::= 17520

    nvmeNamespaceStatusOffline    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "NVMe Namespace Offline."
    ::= 17521

    nvmeNamespaceSpaceOutOfSpace    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "NVMe Namespace Out of Space."
    ::= 17530

    nvmeNamespaceDestroy    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "NVMe Namespace Destroy."
    ::= 17540

    flexGroupConstituentsHaveSpaceIssues    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "FlexGroup Constituents Have Space Issues."
    ::= 17550

    flexGroupConstituentsSpaceStatusAllOK    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "FlexGroup Constituents Space Status All OK."
    ::= 17551

    flexGroupConstituentsHaveInodesIssues    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "FlexGroup Constituents Have Inodes Issues."
    ::= 17560

    flexGroupConstituentsInodesStatusAllOK    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "FlexGroup Constituents Inodes Status All OK."
    ::= 17561

    ocumNvmeNamespaceLatencyIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with NVMe Namespace latency."
    ::= 17562

    ocumNvmeNamespaceLatencyWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with NVMe Namespace latency."
    ::= 17563

    ocumNvmeNamespaceLatencyCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A NVMe Namespace latency incident is cleared."
    ::= 17564

    ocumNvmeNamespaceIopsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with NVMe Namespace IOPS."
    ::= 17565

    ocumNvmeNamespaceIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with NVMe Namespace IOPS."
    ::= 17566

    ocumNvmeNamespaceIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A NVMe Namespace IOPS incident is cleared."
    ::= 17567

    ocumNvmeNamespaceMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with NVMe Namespace MBps."
    ::= 17568

    ocumNvmeNamespaceMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with NVMe Namespace MBps."
    ::= 17569

    ocumNvmeNamespaceMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A NVMe Namespace MBps incident is cleared."
    ::= 17570

    ocumNvmeNamespaceLatencyIopsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with NVMe Namespace latency and IOPS."
    ::= 17571

    ocumNvmeNamespaceLatencyIopsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with NVMe Namespace latency and IOPS."
    ::= 17572

    ocumNvmeNamespaceLatencyIopsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A NVMe Namespace latency and IOPS incident is cleared."
    ::= 17573

    ocumNvmeNamespaceLatencyMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident occurs with NVMe Namespace latency and MBps."
    ::= 17574

    ocumNvmeNamespaceLatencyMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with NVMe Namespace latency and MBps."
    ::= 17575

    ocumNvmeNamespaceLatencyMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A NVMe Namespace latency and MBps incident is cleared."
    ::= 17576

    ocumNvmfFcLifMbpsIncident    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "An incident is occuring with a NVMf FC LIF MBps."
    ::= 17577

    ocumNvmfFcLifMbpsWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning is occuring with a NVMf FC LIF MBps."
    ::= 17578

    ocumNvmfFcLifMbpsCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A NVMf FC LIF MBps incident is cleared."
    ::= 17579

    objectMaintenanceWindowStarted    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Object's Maintenance Window Started."
    ::= 17580

    objectMaintenanceWindowEnded    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Object's Maintenance Window Ended."
    ::= 17581

    ocumDynamicEventWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with dynamic event."
    ::= 17590

    ocumDynamicEventCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A dynamic event warning is cleared."
    ::= 17591

    syncSnapmirrorRelationshipOutofsync    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Synchronous Replication Out Of Sync."
    ::= 17600

    syncSnapmirrorRelationshipInSync    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Synchronous Replication Restored."
    ::= 17601

    syncSnapmirrorRelationshipAutoSyncRetryFailed    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Synchronous Replication Auto Resync Failed."
    ::= 17602

    volumeLogicalSpaceNearlyFull    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Volume Logical Space Nearly Full."
    ::= 17610

    volumeLogicalSpaceFull    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Volume Logical Space Full."
    ::= 17611

    volumeLogicalSpaceAllOK    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Volume Logical Space All OK."
    ::= 17612

    ocumQosVolumeMaxIopsBlocksizePerTbWarning    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A warning occurs with QoS volume max IOPS/TB with Blocksize."
    ::= 17613

    ocumQosVolumeMaxIopsBlocksizePerTbCleared    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "A QoS volume max IOPS/TB with Blocksize warning is cleared."
    ::= 17614

    clusterCapacityTierPlanningWarning   TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Cluster Capacity Tier Planning Warning"
    ::= 17700

    clusterCapacityTierPlanningCleared   TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Cluster Capacity Tier Planning Cleared"
    ::= 17701

    waflVolAutoSizeFail    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "WAFL Volume autoSize failed."
    ::= 17710

    waflVolAutoSizeDone    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "WAFL Volume autoSize is done."
    ::= 17711

    lunDestroy    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "LUN is destroyed."
    ::= 17720

    nbladeCifsManyAuths    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Many CIFS connections occurred."
    ::= 17730

    nbladeCifsMaxOpenSameFile    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Max CIFS Connection Exceeded."
    ::= 17731

    nbladeCifsMaxSessPerUsrConn    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Max Number of CIFS Connection Per User Exceeded."
    ::= 17732

    nbladeCifsNbNameConflict    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "CIFS NetBIOS Name Conflict occurred."
    ::= 17734

    nbladeCifsNoPrivShare    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Attempts to nonexistent CIFS share occurred."
    ::= 17735

    nbladeVscanVirusDetected    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Virus Found By AV Server."
    ::= 17740

    nbladeVscanNoScannerConn    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "No Scanner Connection for Virus Scan."
    ::= 17741

    nbladeVscanNoRegdScanner    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "No AV server Registered."
    ::= 17742

    nbladeVscanConnInactive    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "No Responsive AV Server Connection."
    ::= 17744

    nbladeVscanConnBackPressure    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "AV Server is too Busy to Accept New Scan Request."
    ::= 17745

    nbladeVscanBadUserPrivAccess    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "AV Server is too Busy to Accept New Scan Request."
    ::= 17746

    nbladeNfsv4PoolEXhaust    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "One of NFSv4 Pools Exhausted."
    ::= 17750

    cifsShadowCopyFailure    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "CIFS Shadow Copy Operation Failed."
    ::= 17760

    clusterFabricPoolNearlyFull    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "FabricPool Space is nearly full."
    ::= 17770

    oscSignatureMismatch    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Request mismatches object-store signature."
    ::= 17780

    arlNetraCaCheckFailed    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Object-store Access Denied for Aggregate Relocation."
    ::= 17790

    gbNetraCaCheckFailed    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "Object-store Access Denied for Aggregate Relocation During Storage Failover."
    ::= 17791

    nvmfGracePeriodStart    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "NVMe-oF Grace Period Started"
    ::= 17800

    nvmfGracePeriodActive    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "NVMe-oF Grace Period Is Active"
    ::= 17801

    nvmfGracePeriodExpired    TRAP-TYPE
    ENTERPRISE    netappOnCommandUnifiedManager
    VARIABLES       {
            ocumSystemId,
            ocumEventName,
            ocumEventSeverity,
            ocumEventImpactLevel,
            ocumEventTimestamp,
            ocumEventMessage,
            ocumEventMessageDetails,
            ocumEventSourceResourceKey,
            ocumEventSourceFullName,
            ocumEventSourceType,
            ocumEventSourceHealthStatus,
            ocumEventSourceScopedResourceKey,
            ocumEventSourceScopedFullName,
            ocumEventSourceClusterResourceKey,
            ocumEventSourceClusterFullName,
            ocumEventState
            }
    DESCRIPTION
    "NVMe-oF Grace Period Is Expired"
    ::= 17802

    END
