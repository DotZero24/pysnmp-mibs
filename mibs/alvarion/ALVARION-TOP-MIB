ALVARION-TOP-MIB	DEFINITIONS ::= BEGIN
	IMPORTS
		enterprises FROM RFC1155-SMI;

	alvarion	OBJECT IDENTIFIER
			::=  {  enterprises  12394  }

	products	OBJECT IDENTIFIER
			::=  {  alvarion  1  }

--  rainbow            OBJECT IDENTIFIER ::=  {  products 2 } (see rainbow.mib)
--  rainbowMicroBST    OBJECT IDENTIFIER ::=  {  products 4 } (see MicroBST.mib)
--  breezeMaxTDD       OBJECT IDENTIFIER ::=  {  products 6 } (see rainbow.mib)
--  microBstTDD        OBJECT IDENTIFIER ::=  {  products 8 } (see MicroBST.mib)

END
