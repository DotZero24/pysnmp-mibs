--
--
--                  Rainbow Management Ate MIB
--
--                         03/03/06
--
--
--      =================================

RB-ATE-MIB	DEFINITIONS ::= BEGIN
	IMPORTS
		DisplayString
			FROM SNMPv2-TC
		MODULE-IDENTITY, OBJECT-TYPE, enterprises, Integer32
			FROM SNMPv2-SMI;


	rainbowAteMib	MODULE-IDENTITY
		LAST-UPDATED	"200603031500Z"
		ORGANIZATION	"Alvarion Ltd."
		CONTACT-INFO	"Alvarion Customer Service
		Postal: Alvarion Ltd.
			Barzel 21
			Tel Aviv 69710
			ISRAEL
               	E-mail: CS_Coordinator@alvarion.com"
		DESCRIPTION
				"Rainbow ATE"
		REVISION		"200605051500Z"
		DESCRIPTION
				"Revision 2.5"
		::=  {  rainbow  301  }


	alvarion	OBJECT IDENTIFIER
		::=  {  enterprises  12394  }

	products	OBJECT IDENTIFIER
		::=  {  alvarion  1  }

	rainbow	OBJECT IDENTIFIER
		::=  {  products  2  }


-- ===========================================================================
-- System ATE Parameters
-- ===========================================================================
	rbAteConfig				OBJECT IDENTIFIER		::=  {  rainbowAteMib  1  }
	rbAteClockConfig		OBJECT IDENTIFIER		::=  {  rainbowAteMib  2  }
	rbAteTestResults		OBJECT IDENTIFIER		::=  {  rainbowAteMib  3  }
	rbAteBurnFuncs   		OBJECT IDENTIFIER		::=  {  rainbowAteMib  4  }
	rbAteCleanUpParams 		OBJECT IDENTIFIER		::=  {  rainbowAteMib  5  }
	rbAteManualTests 		OBJECT IDENTIFIER		::=  {  rainbowAteMib  6  }


-- ===========================================================================
-- System ATE Config Parameters
-- ===========================================================================

 	rbAteStartTest	OBJECT-TYPE
		SYNTAX			INTEGER  {
		                           none ( 1 ) ,
		                           startFullTest ( 2 ),
		                           startHostTest ( 3 ),
		                           startC5Test ( 4 )
		                         }
		MAX-ACCESS		read-write
		STATUS			current
		DESCRIPTION
				"To start ATE test perform SET with startFullTest (The NPU will reset and start Full test in ATE mode).
				When startHostTest the NPU will Start the only the host test (no reset)."
		::=  {  rbAteConfig  1  }

 	rbAteExitTest	OBJECT-TYPE
		SYNTAX			INTEGER  {
		                           none ( 1 ) ,
		                           exitTest ( 2 )
		                         }
		MAX-ACCESS		read-write
		STATUS			current
		DESCRIPTION
				"The NPU will reset."
		::=  {  rbAteConfig  2  }

 	rbAteTimeToRunC5Test	OBJECT-TYPE
		SYNTAX			Integer32
		MAX-ACCESS		read-write
		STATUS			current
		DESCRIPTION
				"Time to run C5 test"
		::=  {  rbAteConfig  3  }

 	rbAteTestStatus	OBJECT-TYPE
		SYNTAX			INTEGER  {
		                           readyForTest ( 1 ) ,
		                           testInProgress ( 2 )
		                         }
		MAX-ACCESS		read-only
		STATUS			current
		DESCRIPTION
				"readyForTest - any test can be started."
		::=  {  rbAteConfig  4  }

 	rbAteState	OBJECT-TYPE
		SYNTAX			INTEGER  {
		                           inWorkingMode ( 1 ) ,
		                           inAteTestMode ( 2 )
		                         }
		MAX-ACCESS		read-only
		STATUS			current
		DESCRIPTION
				"inWorkingMode - working mode, inAteTestMode - TEST MODE."
		::=  {  rbAteConfig  5  }

 	rbAteTimeOfLastC5Test	OBJECT-TYPE
		SYNTAX			DisplayString (SIZE (1..32))
		MAX-ACCESS		read-only
		STATUS			current
		DESCRIPTION
				"The time the last test started ( SET to rbAteStartTest was done). Format: dd-mm-yy hh:mm:ss"
		::=  {  rbAteConfig  6  }

 	rbAteSnmpRelaySupport	OBJECT-TYPE
		SYNTAX			INTEGER  { unknown ( 0 ) ,
		                           relayOn ( 1 ) ,
		                           relayOff ( 2 )
		                         }
		MAX-ACCESS		read-write
		STATUS			current
		DESCRIPTION
				"rbAteSnmpRelaySupport - relay SNMP messages to AU/SU ON/OFF.
				 Relaying is done according to community:
				 @ATE@@AU.x = relay to AU in slot x.
				 @ATE@@SU.xx-xx-xx-xx-xx-xx = relay to SU with MAC xx-xx-xx-xx-xx-xx."
		::=  {  rbAteConfig  7  }


-- ===========================================================================
-- System ATE Clock Setting Parameters
-- ===========================================================================

 	rbAteDateDay	OBJECT-TYPE
		SYNTAX			Integer32
		MAX-ACCESS		read-write
		STATUS			current
		DESCRIPTION
				"For reading or setting the date."
		::=  {  rbAteClockConfig  1  }

 	rbAteDateDayOfWeek	OBJECT-TYPE
		SYNTAX			INTEGER  {
		                           monday ( 1 ) ,
		                           tuesday ( 2 ) ,
		                           wednesday ( 3 ) ,
		                           thursday ( 4 ) ,
		                           friday ( 5 ) ,
		                           saturday ( 6 ) ,
		                           sunday ( 7 )
		                         }
		MAX-ACCESS		read-write
		STATUS			current
		DESCRIPTION
				"For reading or setting the date."
		::=  {  rbAteClockConfig  2  }

 	rbAteDateMonth	OBJECT-TYPE
		SYNTAX			Integer32
		MAX-ACCESS		read-write
		STATUS			current
		DESCRIPTION
				"For reading or setting the date."
		::=  {  rbAteClockConfig  3  }

 	rbAteDateYear	OBJECT-TYPE
		SYNTAX			Integer32
		MAX-ACCESS		read-write
		STATUS			current
		DESCRIPTION
				"For reading or setting the date."
		::=  {  rbAteClockConfig  4  }

 	rbAteDateHour	OBJECT-TYPE
		SYNTAX			Integer32
		MAX-ACCESS		read-write
		STATUS			current
		DESCRIPTION
				"For reading or setting the time of day."
		::=  {  rbAteClockConfig  5  }

 	rbAteDateMin	OBJECT-TYPE
		SYNTAX			Integer32
		MAX-ACCESS		read-write
		STATUS			current
		DESCRIPTION
				"For reading or setting the time of day."
		::=  {  rbAteClockConfig  6  }

 	rbAteDateSec	OBJECT-TYPE
		SYNTAX			Integer32
		MAX-ACCESS		read-write
		STATUS			current
		DESCRIPTION
				"For reading or setting the time of day."
		::=  {  rbAteClockConfig  7  }


-- ===========================================================================
-- System ATE Result Parameters
-- ===========================================================================

	rbAteTestResultsTable	OBJECT-TYPE
		SYNTAX		SEQUENCE  OF  RbAteTestResultsEntry
		MAX-ACCESS	not-accessible
		STATUS		current
		DESCRIPTION
			"Table to get all Test Results."
		::=  { rbAteTestResults  1 }

	rbAteTestResultsEntry	OBJECT-TYPE
		SYNTAX		RbAteTestResultsEntry
		MAX-ACCESS	not-accessible
		STATUS		current
		DESCRIPTION
			"Row Description."
		INDEX		{  rbAteTestType  }
		::=  { rbAteTestResultsTable 1 }

	RbAteTestResultsEntry  ::=  SEQUENCE {
		rbAteTestType               INTEGER,
		rbAteTestResult             INTEGER,
		rbAteTestResultVal          Integer32,
		rbAteTestResultDescription  DisplayString
		}

 	rbAteTestType	OBJECT-TYPE
		SYNTAX			INTEGER  {
		                           flashMemoryTest   ( 1 ) ,
		                           sdRAMMemoryTest   ( 2 ) ,
		                           watchDogTest      ( 3 ) ,
		                           diskOnChipMemoryTest ( 4 ) ,
		                           tempSensorTest    ( 5 ) ,
		                           i2CBusIntTest     ( 6 ) ,
		                           rs232MonitorTest  ( 7 ) ,
		                           alarmsInOutTest   ( 8 ) ,
		                           acmInOutTest      ( 9 ) ,
		                           gpsTest           ( 10 ) ,
		                           bstSyncTest       ( 11 ) ,
		                           mhzAnd1pps        ( 12 ) ,
		                           bitDcpTest        ( 13 ) ,
		                           bitDcpPhyTest     ( 14 ) ,
		                           bitDcpTluHashTest ( 15 ) ,
		                           bitExt1PPSTest    ( 16 ) ,
		                           gpsRS422Test      ( 17 )
		                         }
		MAX-ACCESS		read-only
		STATUS			current
		DESCRIPTION
				"Type Of Test."
		::=  {  rbAteTestResultsEntry  1  }

 	rbAteTestResult	OBJECT-TYPE
		SYNTAX			INTEGER  {
		                           success ( 0 ) ,
		                           failed ( 1 )
		                         }
		MAX-ACCESS		read-only
		STATUS			current
		DESCRIPTION
				"Last Test Result."
		::=  {  rbAteTestResultsEntry  2  }

 	rbAteTestResultVal	OBJECT-TYPE
		SYNTAX			Integer32
		MAX-ACCESS		read-only
		STATUS			current
		DESCRIPTION
				"Last Test Result Value."
		::=  {  rbAteTestResultsEntry  3  }

 	rbAteTestResultDescription	OBJECT-TYPE
		SYNTAX			DisplayString (SIZE (1..255))
		MAX-ACCESS		read-only
		STATUS			current
		DESCRIPTION
				"Test Result Description."
		::=  {  rbAteTestResultsEntry  4  }


-- ===========================================================================
-- System Burn Parameters
-- ===========================================================================

 	rbAteEnterSerialNum	OBJECT-TYPE
		SYNTAX			DisplayString (SIZE (1..32))
		MAX-ACCESS		read-write
		STATUS			current
		DESCRIPTION
				"To start ATE burn functionality! locked after first burn."
		::=  {  rbAteBurnFuncs  1  }

 	rbAteEnterMacAddress	OBJECT-TYPE
		SYNTAX			DisplayString (SIZE (1..12))
		MAX-ACCESS		read-write
		STATUS			current
		DESCRIPTION
				"To start ATE burn functionality! locked after first burn."
		::=  {  rbAteBurnFuncs  2  }


-- ===========================================================================
-- ATE Cleanup Params
-- ===========================================================================

 	rbAteDeleteNpuShadowFile	OBJECT-TYPE
		SYNTAX			INTEGER  {
		                           none ( 1 ) ,
		                           delete ( 2 )
		                         }
		MAX-ACCESS		read-write
		STATUS			current
		DESCRIPTION
				"Deletes the existing file name."
		::=  {  rbAteCleanUpParams  1  }

 	rbAteSetServiceDefault	OBJECT-TYPE
		SYNTAX			INTEGER  {
		                           none ( 1 ) ,
		                           setDefault ( 2 )
		                         }
		MAX-ACCESS		read-write
		STATUS			current
		DESCRIPTION
				"Sets a Services to default and reboots NPU."
		::=  {  rbAteCleanUpParams  2  }

 	rbAtePowerOnCntReset	OBJECT-TYPE
		SYNTAX			INTEGER  {
		                           none ( 1 ) ,
		                           reset ( 2 )
		                         }
		MAX-ACCESS		read-write
		STATUS			current
		DESCRIPTION
				"Resets the Cumulative Power On Time Counter."
		::=  {  rbAteCleanUpParams  3  }


-- ===========================================================================
-- System ATE Manual Tests
-- ===========================================================================

 	rbAteStartDcpTluHashTest	OBJECT-TYPE
		SYNTAX			INTEGER  {
		                           none ( 1 ) ,
		                           startTest ( 2 )
		                         }
		MAX-ACCESS		read-write
		STATUS			current
		DESCRIPTION
				"Start Dcp Tlu Hash Trie key Test. Result will be in the Results table."
		::=  {  rbAteManualTests  1  }

 	rbAteStartGpsExt1PPSTest	OBJECT-TYPE
		SYNTAX			INTEGER  {
		                           none ( 1 ) ,
		                           startTest ( 2 )
		                         }
		MAX-ACCESS		read-write
		STATUS			current
		DESCRIPTION
				"Start GPS External1PPS Test. Result will be in the Results table."
		::=  {  rbAteManualTests  2  }

 	rbAteStartGpsRS422Test	OBJECT-TYPE
		SYNTAX			INTEGER  {
		                           none ( 1 ) ,
		                           startTest ( 2 )
		                         }
		MAX-ACCESS		read-write
		STATUS			current
		DESCRIPTION
				"Start Gps RS422 Test. Result will be in the Results table."
		::=  {  rbAteManualTests  3  }


END
