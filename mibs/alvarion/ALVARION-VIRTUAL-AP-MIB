-- ****************************************************************************
--  ALVARION-VIRTUAL-AP-MIB definitions
--
--  Copyright (c) 2007, Alvarion Ltd.
--  All Rights Reserved.
--
--  Alvarion Virtual Access Point MIB file.
--
-- ****************************************************************************


ALVARION-VIRTUAL-AP-MIB DEFINITIONS ::= BEGIN

IMPORTS
    MODULE-IDENTITY, OBJECT-TYPE,
    Integer32
        FROM    SNMPv2-SMI
    TruthValue
        FROM    SNMPv2-TC
    MODULE-COMPLIANCE, OBJECT-GROUP
        FROM    SNMPv2-CONF
    ifIndex
        FROM    IF-MIB
    alvarionMgmtV2
        FROM    ALVARION-SMI
    AlvarionSSID, AlvarionUsersAuthenticationMode,
    AlvarionProfileIndexOrZero, AlvarionSecurity,
    AlvarionPriorityQueue
        FROM    ALVARION-TC
;


alvarionVirtualApMIB   MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Alvarion Virtual Access Point MIB."

    ::= { alvarionMgmtV2 11 }


-- alvarionVirtualApMIB definition
alvarionVirtualApMIBObjects OBJECT IDENTIFIER ::= { alvarionVirtualApMIB 1 }

-- alvarion Virtual Access Point groups
coVirtualApConfig    OBJECT IDENTIFIER ::= { alvarionVirtualApMIBObjects 1 }


-- The Virtual Access Point Address Configuration Group
coVirtualAccessPointConfigTable OBJECT-TYPE
    SYNTAX      SEQUENCE OF CoVirtualAccessPointConfigEntry
    MAX-ACCESS  not-accessible
    STATUS      current
    DESCRIPTION "VSC  configuration attributes. In tabular form to
                 allow for multiple instances."
    ::= { coVirtualApConfig 1 }

coVirtualAccessPointConfigEntry OBJECT-TYPE
    SYNTAX      CoVirtualAccessPointConfigEntry
    MAX-ACCESS  not-accessible
    STATUS      current
    DESCRIPTION "An entry in the coVirtualAccessPointConfigTable.
                 ifIndex - Each 802.11 interface is represented by an ifEntry.
                           Interface tables in this MIB module are indexed by
                           ifIndex.
                 coVirtualWlanProfileIndex - Uniquely access a profile for this
                                             particular 802.11 interface."
    INDEX       { ifIndex, coVirtualApWlanProfileIndex }
    ::= { coVirtualAccessPointConfigTable 1 }

CoVirtualAccessPointConfigEntry ::= SEQUENCE
{
    coVirtualApWlanProfileIndex                  Integer32,
    coVirtualApSSID                              AlvarionSSID,
    coVirtualApBroadcastSSID                     TruthValue,
    coVirtualApMaximumNumberOfUsers              Integer32,
    coVirtualApDefaultVLAN                       Integer32,
    coVirtualApSecurity                          AlvarionSecurity,
    coVirtualApAuthenMode                        AlvarionUsersAuthenticationMode,
    coVirtualApAuthenProfileIndex                AlvarionProfileIndexOrZero,
    coVirtualApUserAccountingEnabled             INTEGER,
    coVirtualApUserAccountingProfileIndex        AlvarionProfileIndexOrZero,
    coVirtualApDefaultUserRateLimitationEnabled  TruthValue,
    coVirtualApDefaultUserMaxTransmitRate        Integer32,
    coVirtualApDefaultUserMaxReceiveRate         Integer32,
    coVirtualApDefaultUserBandwidthLevel         AlvarionPriorityQueue,
    coVirtualApOperState                         INTEGER
}

coVirtualApWlanProfileIndex OBJECT-TYPE
    SYNTAX      Integer32 (1..2147483647)
    MAX-ACCESS  not-accessible
    STATUS      current
    DESCRIPTION "Specifies the index of the VSC profile."
    ::= { coVirtualAccessPointConfigEntry 1 }

coVirtualApSSID OBJECT-TYPE
    SYNTAX      AlvarionSSID
    MAX-ACCESS  read-write
    STATUS      current
    DESCRIPTION "Service Set ID assigned to the VSC. This value must be
                 unique per radio interface."
    ::= { coVirtualAccessPointConfigEntry 2 }

coVirtualApBroadcastSSID OBJECT-TYPE
    SYNTAX      TruthValue
    MAX-ACCESS  read-write
    STATUS      current
    DESCRIPTION "Specifies if the SSID is included in beacon frames.
                 On Intersil hardware, only the first profile is
                 manageable. Reading this attribute shall always return
                 'false' for the other profiles. Writing into this attribute
                 for the other profiles will return an error."
    ::= { coVirtualAccessPointConfigEntry 3 }

coVirtualApMaximumNumberOfUsers OBJECT-TYPE
    SYNTAX      Integer32 (1..255)
    MAX-ACCESS  read-write
    STATUS      current
    DESCRIPTION "Specifies the maximum number of concurrent users that this
                 profile can accept."
    ::= { coVirtualAccessPointConfigEntry 4 }

coVirtualApDefaultVLAN OBJECT-TYPE
    SYNTAX      Integer32 (0..4094)
    MAX-ACCESS  read-write
    STATUS      current
    DESCRIPTION "Specifies the default VLAN to use for this profile
                 when no radius authentication has taken place.
                 The value 0 is used when no VLAN has been assigned to this
                 profile. Writing to this object is only available on
                 satellite devices."
    ::= { coVirtualAccessPointConfigEntry 5 }

coVirtualApSecurity OBJECT-TYPE
    SYNTAX      AlvarionSecurity
    MAX-ACCESS  read-only
    STATUS      current
    DESCRIPTION "Identifies all supported authentication/encryption algorithms."
    ::= { coVirtualAccessPointConfigEntry 6 }

coVirtualApAuthenMode OBJECT-TYPE
    SYNTAX      AlvarionUsersAuthenticationMode
    MAX-ACCESS  read-only
    STATUS      current
    DESCRIPTION "Specifies if user authentication is performed locally or via
                 an AAA server."
    ::= { coVirtualAccessPointConfigEntry 7 }

coVirtualApAuthenProfileIndex OBJECT-TYPE
    SYNTAX      AlvarionProfileIndexOrZero
    MAX-ACCESS  read-only
    STATUS      current
    DESCRIPTION "Specifies the AAA server profile to use for user authentication.
                 This parameter only applies when the coVirtualApSecurity
                 is set to 'wpa' or 'ieee802dot1x' or 'ieee802dot1xWithWep' and
                 the coVirtualApAuthenMode set to 'profile' or
                 'localAndProfile'. When set to Zero, no AAA server profile
                 is selected or on a public satellite device it could represent
                 a pre-configured AAA profile."
    ::= { coVirtualAccessPointConfigEntry 8 }

coVirtualApUserAccountingEnabled OBJECT-TYPE
    SYNTAX      INTEGER
                {
                    enable(1),
                    disable(2)
                }
    MAX-ACCESS  read-only
    STATUS      current
    DESCRIPTION "Indicates if accounting information is generated by the
                 device and sent to the AAA server for users connecting to
                 this profile. Accounting information will be generated only
                 if a valid AAA server profile is configured for the
                 coVirtualApAccountingProfileIndex attribute."
    ::= { coVirtualAccessPointConfigEntry 9 }

coVirtualApUserAccountingProfileIndex OBJECT-TYPE
    SYNTAX      AlvarionProfileIndexOrZero
    MAX-ACCESS  read-only
    STATUS      current
    DESCRIPTION "Identifies the AAA server profile to be used for accounting
                 information. The special value Zero indicates that no accounting
                 profile is selected."
    ::= { coVirtualAccessPointConfigEntry 10 }

coVirtualApDefaultUserRateLimitationEnabled OBJECT-TYPE
    SYNTAX      TruthValue
    MAX-ACCESS  read-only
    STATUS      current
    DESCRIPTION "Indicates if the default user rate limitation is enabled."
    ::= { coVirtualAccessPointConfigEntry 11 }

coVirtualApDefaultUserMaxTransmitRate OBJECT-TYPE
    SYNTAX      Integer32
    MAX-ACCESS  read-only
    STATUS      current
    DESCRIPTION "Identifies the default user maximum transmit rate."
    ::= { coVirtualAccessPointConfigEntry 12 }

coVirtualApDefaultUserMaxReceiveRate OBJECT-TYPE
    SYNTAX      Integer32
    MAX-ACCESS  read-only
    STATUS      current
    DESCRIPTION "Identifies the default user maximum receive rate."
    ::= { coVirtualAccessPointConfigEntry 13 }

coVirtualApDefaultUserBandwidthLevel OBJECT-TYPE
    SYNTAX      AlvarionPriorityQueue
    MAX-ACCESS  read-only
    STATUS      current
    DESCRIPTION "Identifies the default user bandwidth level."
    ::= { coVirtualAccessPointConfigEntry 14 }

coVirtualApOperState OBJECT-TYPE
    SYNTAX      INTEGER
                {
                    enable(1),
                    disable(2)
                }
    MAX-ACCESS  read-write
    STATUS      current
    DESCRIPTION "Activate/Deactivate the Virtual Service Community in
                 the radio."
    ::= { coVirtualAccessPointConfigEntry 15 }


-- conformance information
alvarionVirtualApMIBConformance OBJECT IDENTIFIER ::= { alvarionVirtualApMIB 2 }
alvarionVirtualApMIBCompliances OBJECT IDENTIFIER ::= { alvarionVirtualApMIBConformance 1 }
alvarionVirtualApMIBGroups      OBJECT IDENTIFIER ::= { alvarionVirtualApMIBConformance 2 }


-- compliance statements
alvarionVirtualApMIBCompliance MODULE-COMPLIANCE
    STATUS      current
    DESCRIPTION "The compliance statement for the Virtual Access Point MIB."
    MODULE      MANDATORY-GROUPS
                    {
                        alvarionVirtualApMIBGroup
                    }
    ::= { alvarionVirtualApMIBCompliances 1 }

-- units of conformance
alvarionVirtualApMIBGroup OBJECT-GROUP
    OBJECTS     {
                    coVirtualApSSID,
                    coVirtualApBroadcastSSID,
                    coVirtualApMaximumNumberOfUsers,
                    coVirtualApDefaultVLAN,
                    coVirtualApSecurity,
                    coVirtualApAuthenMode,
                    coVirtualApAuthenProfileIndex,
                    coVirtualApUserAccountingEnabled,
                    coVirtualApUserAccountingProfileIndex,
                    coVirtualApDefaultUserRateLimitationEnabled,
                    coVirtualApDefaultUserMaxTransmitRate,
                    coVirtualApDefaultUserMaxReceiveRate,
                    coVirtualApDefaultUserBandwidthLevel,
                    coVirtualApOperState
                }
    STATUS      current
    DESCRIPTION "A collection of objects for use with Virtual Access Points."
    ::= { alvarionVirtualApMIBGroups 1 }

END
