-- ============================================================
-- Description :
--
--          Rainbow Notifications Management Information Base
--
--                         06/06/2006
--
--
-- ============================================================

RAINBOW-NOTIFICATIONS-MIB	DEFINITIONS ::= BEGIN
	IMPORTS
		rainbow, rbTrapSeqNumber,rbTrapSource,rbTrapSeverity,rbTrapCategory,rbTrapAdditionalInfo,
		rbChannelId,rbSuTxPower,rbLicenseId,rbSuMacAddr,rbSuSysName,rbTrapLedStatus,rbTrapIpAddress,
		rbTrapSetFailureReason
			FROM RAINBOW-MIB
		rbServiceIdx, rbServiceName, rbSubscriberIdx, rbSubscriberID
 		    FROM RAINBOW-SERVICES-MIB
		rbRadiusAuthServerAddress, rbRadiusAcctServerAddress
 		    FROM RAINBOW-RADIUS-MIB
		MODULE-IDENTITY, NOTIFICATION-TYPE
			FROM SNMPv2-SMI;

--  enterprises  OBJECT IDENTIFIER ::=
--  { iso org(3) dod(6) internet(1) private(4) 1 }
--  alvarion     OBJECT IDENTIFIER ::=  { enterprises 12394 }
--  products     OBJECT IDENTIFIER ::=  { alvarion 1 }
--  rainbow      OBJECT IDENTIFIER ::=  { products 2 }


	rbNotifications	MODULE-IDENTITY
		LAST-UPDATED	"200606061500Z"
		ORGANIZATION	"Alvarion Ltd."
		CONTACT-INFO	"Alvarion Customer Service
		Postal: Alvarion Ltd.
			Barzel 21
			Tel Aviv 69710
			ISRAEL
               	E-mail: CS_Coordinator@alvarion.com"
		DESCRIPTION
				"Rainbow notifications MIB Definitions"
		REVISION		"200606061500Z"
		DESCRIPTION
				"Release 2.5"
		::=  {  rainbow  0 }


 --========================================================================
-- General Traps
--========================================================================

   rbResetOn    NOTIFICATION-TYPE
        OBJECTS {
                rbTrapSeqNumber,
                rbTrapSource,
                rbTrapSeverity,
                rbTrapCategory,
                rbTrapAdditionalInfo
                }
	    STATUS current
	    DESCRIPTION	"This trap is sent when the device/card is going to perform reset.
				rbTrapSource = NPU/AU/SU
	    		rbTrapSeverity = Info
				rbTrapCategory = Equipment
				rbTrapAdditionalInfo = 1..2  for external/internal fault."
        ::= { rbNotifications 1 }

    rbDiagnosticsHwFaultOn    NOTIFICATION-TYPE
        OBJECTS {
                rbTrapSeqNumber,
                rbTrapSource,
                rbTrapSeverity,
                rbTrapCategory,
                rbTrapAdditionalInfo,
				rbTrapLedStatus
				}
   	    STATUS current
	    DESCRIPTION	"Device/card has detected hardware fault.
				rbTrapSource = 	NPU/AU/SU
	    		rbTrapSeverity = Major
				rbTrapCategory = Equipment
				rbTrapAdditionalInfo = 3..8,23..27."
        ::= { rbNotifications 2 }

    rbDiagnosticsHwFaultOff    NOTIFICATION-TYPE
        OBJECTS {
                rbTrapSeqNumber,
                rbTrapSource,
                rbTrapSeverity,
                rbTrapCategory,
                rbTrapAdditionalInfo,
                rbTrapLedStatus }
   	    STATUS current
	    DESCRIPTION	"Previously detected hardware fault is fixed.
				rbTrapSource = 	NPU/AU/SU
	    		rbTrapSeverity = Info
				rbTrapCategory = Equipment
				rbTrapAdditionalInfo = 3..8,23..27."
        ::= { rbNotifications 3 }

    rbMonitorAccessOn    NOTIFICATION-TYPE
        OBJECTS {
                rbTrapSeqNumber,
                rbTrapSource,
                rbTrapSeverity,
                rbTrapCategory,
				rbTrapAdditionalInfo,
				rbTrapIpAddress }
   	    STATUS current
	    DESCRIPTION	"Device is accessed via LCI or Telnet.
				rbTrapSource = 	NPU/SU
	    		rbTrapSeverity = Info,
				rbTrapCategory = Equipment,
				rbTrapAdditionalInfo = 140,141,
				rbTrapIpAddress "
        ::= { rbNotifications 4 }

    rbMonitorAccessOff    NOTIFICATION-TYPE
        OBJECTS {
                rbTrapSeqNumber,
                rbTrapSource,
                rbTrapSeverity,
                rbTrapCategory,
				rbTrapAdditionalInfo,
				rbTrapIpAddress }
   	    STATUS current
	    DESCRIPTION	"LCI or Telnet access was terminated
				rbTrapSource = 	NPU/SU
	    		rbTrapSeverity = Info,
				rbTrapCategory = Equipment,
				rbTrapAdditionalInfo = 140,141,
				rbTrapIpAddress "
        ::= { rbNotifications 5 }

    rbAuNetworkEntryStatus    NOTIFICATION-TYPE
        OBJECTS {
                rbTrapSeqNumber,
                rbTrapSource,
                rbTrapSeverity,
                rbTrapCategory,
				rbTrapAdditionalInfo
                }
	    STATUS current
	    DESCRIPTION	"AU Network Entry status changed
				rbTrapSource = 	AU
	    		rbTrapSeverity = Info,
				rbTrapCategory = Communication,
				rbTrapAdditionalInfo = 135-139  "
        ::= { rbNotifications 6 }

    rbModeConflictOn    NOTIFICATION-TYPE
        OBJECTS {
                rbTrapSeqNumber,
                rbTrapSource,
                rbTrapSeverity,
                rbTrapCategory,
				rbTrapAdditionalInfo
                }
	    STATUS current
	    DESCRIPTION	"AU/SU mode conflict was detected
				rbTrapSource = 	AU/SU
	    		rbTrapSeverity = Major,
				rbTrapCategory = Communication,
				rbTrapAdditionalInfo = 144 .. 149."
        ::= { rbNotifications 7 }

    rbModeConflictOff    NOTIFICATION-TYPE
        OBJECTS {
                rbTrapSeqNumber,
                rbTrapSource,
                rbTrapSeverity,
                rbTrapCategory,
				rbTrapAdditionalInfo
                }
	    STATUS current
	    DESCRIPTION	"AU/SU mode conflict terminated
				rbTrapSource = 	AU/SU
	    		rbTrapSeverity = Info,
				rbTrapCategory = Communication,
				rbTrapAdditionalInfo = 144."
        ::= { rbNotifications 8 }


--========================================================================
--	 Shelf Related Traps    21..40
--========================================================================

    rbShelfCardExtractionOn    NOTIFICATION-TYPE
        OBJECTS {
                rbTrapSeqNumber,
                rbTrapSource,
                rbTrapSeverity,
                rbTrapCategory
                }
	    STATUS current
	    DESCRIPTION	"Card is extracted from the shelf.
				rbTrapSource = NPU/AU/PSU/PIU/ACU
	    		rbTrapSeverity = Info,
				rbTrapCategory = Equipment "
        ::= { rbNotifications 21 }

    rbShelfCardInsertionOn    NOTIFICATION-TYPE
        OBJECTS {
                rbTrapSeqNumber,
                rbTrapSource,
                rbTrapSeverity,
                rbTrapCategory
                }
	    STATUS current
	    DESCRIPTION	"Card is inserted in the shelf.
				rbTrapSource = NPU/AU/PSU/PIU/ACU
	    		rbTrapSeverity = Info,
				rbTrapCategory = Equipment"
        ::= { rbNotifications 22 }

    rbShelfPeripheralEquipmentFaultOn    NOTIFICATION-TYPE
        OBJECTS {
                rbTrapSeqNumber,
                rbTrapSource,
                rbTrapSeverity,
                rbTrapCategory,
                rbTrapAdditionalInfo
                }
	    STATUS current
	    DESCRIPTION	"Fault is detected in one of the Shelf Peripheral Equipment Units.
				rbTrapSource = PSU#/PIU#/ACU#/ACU-FAN#/AU
	    		rbTrapSeverity = Minor,
				rbTrapCategory = Equipment
				rbTrapAdditionalInfo = 53..55"
        ::= { rbNotifications 23 }

    rbShelfPeripherallEquipmentFaultOff     NOTIFICATION-TYPE
        OBJECTS {
                rbTrapSeqNumber,
                rbTrapSource,
                rbTrapSeverity,
                rbTrapCategory,
                rbTrapAdditionalInfo
                }
	    STATUS current
	    DESCRIPTION	"Previously detected fault in one of the shelf Peripheral Equipment Units is terminated.
				rbTrapSource = PSU#/PIU#/ACU#/AU
	    		rbTrapSeverity = Info,
				rbTrapCategory = Equipment
				rbTrapAdditionalInfo = 53..55"
        ::= { rbNotifications 24 }

    rbShelfEnvParamFaultOn    NOTIFICATION-TYPE
        OBJECTS {
                rbTrapSeqNumber,
                rbTrapSource,
                rbTrapSeverity,
                rbTrapCategory,
                rbTrapAdditionalInfo
                 }
	    STATUS current
	    DESCRIPTION	"Fault is detected in the shelf environment parameter.
				rbTrapSource = 	NPU
	    		rbTrapSeverity = Info,
				rbTrapCategory = Equipment
				rbTrapAdditionalInfo = 73..76"
        ::= { rbNotifications 25 }

    rbShelfEnvParamFaultOff    NOTIFICATION-TYPE
        OBJECTS {
                rbTrapSeqNumber,
                rbTrapSource,
                rbTrapSeverity,
                rbTrapCategory,
                rbTrapAdditionalInfo }
	    STATUS current
	    DESCRIPTION	"Previously detected environment parameter fault is terminated.
				rbTrapSource = 	NPU
	    		rbTrapSeverity = Info,
				rbTrapCategory = Equipment
				rbTrapAdditionalInfo = 73..76"
        ::= { rbNotifications 26 }


--========================================================================
--   NPU/MBST Related Traps		   41 ..60
--========================================================================

    rbConfigurationChanged    NOTIFICATION-TYPE
        OBJECTS {
                rbTrapSeqNumber,
                rbTrapSource,
                rbTrapSeverity,
                rbTrapCategory,
                rbTrapAdditionalInfo
                }
	    STATUS current
	    DESCRIPTION	"Configuration change was detected,
				rbTrapSource = 	NPU/AU/SU/RC/ODU/CHNL/SBSCR/SRVC
	    		rbTrapSeverity = Info,
				rbTrapCategory = Equipment
				rbTrapAdditionalInfo = 30..33."
        ::= { rbNotifications 41 }

    rbParameterSetFailure    NOTIFICATION-TYPE
        OBJECTS {
                rbTrapSeqNumber,
                rbTrapSource,
                rbTrapSeverity,
                rbTrapCategory,
                rbTrapSetFailureReason
                }
	    STATUS current
	    DESCRIPTION	"Configuration change was detected,
				rbTrapSource = 	NPU/AU/SU
	    		rbTrapSeverity = Info,
				rbTrapCategory = Equipment
				rbTrapSetFailureReason."
        ::= { rbNotifications 42 }

    rbMbstLicense    NOTIFICATION-TYPE
        OBJECTS {
                rbTrapSeqNumber,
                rbTrapSource,
                rbTrapSeverity,
                rbTrapCategory,
				rbTrapAdditionalInfo
                }
	    STATUS current
	    DESCRIPTION	"License Grace Period expiration warning,
				rbTrapSource = 	MicroBST
	    		rbTrapSeverity = Info,
				rbTrapCategory = Proc,
				rbTrapAdditionalInfo = 184,185."
        ::= { rbNotifications 50 }

    rbMbstCPEQuantityExceed    NOTIFICATION-TYPE
        OBJECTS {
                rbTrapSeqNumber,
                rbTrapSource,
                rbTrapSeverity,
                rbTrapCategory,
				rbSuMacAddr
                }
	    STATUS current
	    DESCRIPTION	"Allowed quantity of CPEs exceeded in the actual Mbst,
				rbTrapSource = 	MicroBST
	    		rbTrapSeverity = Info,
				rbTrapCategory = Proc,
				rbSuMacAddr = Rejected SU Mac"
        ::= { rbNotifications 51 }

    rbLicenseFileLoadStatus    NOTIFICATION-TYPE
        OBJECTS {
                rbTrapSeqNumber,
                rbTrapSource,
                rbTrapSeverity,
                rbTrapCategory,
                rbTrapAdditionalInfo
                }
	    STATUS current
	    DESCRIPTION	"License File Load process status,
				rbTrapSource = 	NPU/MicroBST
	    		rbTrapSeverity = Info,
				rbTrapCategory = Proc,
				rbTrapAdditionalInfo = 187..191"
        ::= { rbNotifications 52 }


--========================================================================
--	   ODU Related Traps		 61 .. 80
--========================================================================

    rbOduCrcErrorOn    NOTIFICATION-TYPE
        OBJECTS {
                rbTrapSeqNumber,
                rbTrapSource,
                rbTrapSeverity,
                rbTrapCategory,
				rbChannelId
                }
	    STATUS obsolete
	    DESCRIPTION	"Obsolete from release 2.5
	            CRC error in the ODU table was detected,
				rbTrapSource = 	AU
				rbTrapSeverity = Warning,
				rbTrapCategory = Communication,
				rbChannelId = number of channel "
        ::= { rbNotifications 61 }

    rbOduCrcErrorOff    NOTIFICATION-TYPE
        OBJECTS {
                rbTrapSeqNumber,
                rbTrapSource,
                rbTrapSeverity,
                rbTrapCategory,
				rbChannelId
                }
	    STATUS obsolete
	    DESCRIPTION	"Obsolete from release 2.5
	            Previously detected CRC error in ODU table terminated,
				rbTrapSource = AU
	    		rbTrapSeverity = Info,
				rbTrapCategory = Communication,
				rbChannelId = number of channel "
        ::= { rbNotifications 62 }

    rbOduCommErrorOn    NOTIFICATION-TYPE
        OBJECTS {
                rbTrapSeqNumber,
                rbTrapSource,
                rbTrapSeverity,
                rbTrapCategory,
				rbChannelId
                }
	    STATUS current
	    DESCRIPTION	"Error in the communication with the ODU unit was detected,
				rbTrapSource = 	AU
	    		rbTrapSeverity = Minor,
				rbTrapCategory = Communication,
				rbChannelId = number of channel "
        ::= { rbNotifications 63 }

    rbOduCommErrorOff    NOTIFICATION-TYPE
        OBJECTS {
                rbTrapSeqNumber,
                rbTrapSource,
                rbTrapSeverity,
                rbTrapCategory,
				rbChannelId
                }
	    STATUS current
	    DESCRIPTION	"Previously detected ODU communication error terminated,
				rbTrapSource = 	AU,
	    		rbTrapSeverity = Info,
				rbTrapCategory = Communication,
				rbChannelId = number of channel "
        ::= { rbNotifications 64 }

    rbOduBandMissmatchOn    NOTIFICATION-TYPE
        OBJECTS {
                rbTrapSeqNumber,
                rbTrapSource,
                rbTrapSeverity,
                rbTrapCategory,
				rbChannelId
                }
	    STATUS current
	    DESCRIPTION	"Actual ODU Band does not match configured ODU Band,
				rbTrapSource = 	AU,
	    		rbTrapSeverity = Major,
				rbTrapCategory = Communication,
				rbChannelId = number of channel "
        ::= { rbNotifications 65 }

    rbOduBandMissmatchOff    NOTIFICATION-TYPE
        OBJECTS {
                rbTrapSeqNumber,
                rbTrapSource,
                rbTrapSeverity,
                rbTrapCategory,
				rbChannelId
                }
	    STATUS current
	    DESCRIPTION	"Previously detected ODU Band mismatch terminated,
				rbTrapSource = 	AU,
	    		rbTrapSeverity = Info,
				rbTrapCategory = Communication,
				rbChannelId = number of channel "
        ::= { rbNotifications 66 }

    rbOduPowerMismatch    NOTIFICATION-TYPE
        OBJECTS {
                rbTrapSeqNumber,
                rbTrapSource,
                rbTrapSeverity,
                rbTrapCategory,
		        rbChannelId
                }
	    STATUS current
	    DESCRIPTION	"Actual ODU Max/Min Tx power does not match configured ODU Max/Min Tx power,
				rbTrapSource = 	AU,
	    		rbTrapSeverity = Info,
				rbTrapCategory = Communication,
				rbChannelId = number of channel "
        ::= { rbNotifications 67 }

    rbOduFailureOn    NOTIFICATION-TYPE
        OBJECTS {
                rbTrapSeqNumber,
                rbTrapSource,
                rbTrapSeverity,
                rbTrapCategory,
				rbChannelId,
                rbTrapAdditionalInfo
                }
	    STATUS current
	    DESCRIPTION	"ODU unit failure was detected,
				rbTrapSource = 	AU
	    		rbTrapSeverity = Major,
				rbTrapCategory = Communication,
				rbChannelId = number of channel,
				rbTrapAdditionalInfo = 225..228"
        ::= { rbNotifications 68 }

    rbOduFailureOff    NOTIFICATION-TYPE
        OBJECTS {
                rbTrapSeqNumber,
                rbTrapSource,
                rbTrapSeverity,
                rbTrapCategory,
				rbChannelId
                }
	    STATUS current
	    DESCRIPTION	"Previously detected ODU failure terminated,
				rbTrapSource = 	AU,
	    		rbTrapSeverity = Info,
				rbTrapCategory = Communication,
				rbChannelId = number of channel "
        ::= { rbNotifications 69 }


--========================================================================
--    SU Related Traps		   81 .. 100
--========================================================================

    rbSuMaxTxPowerReached    NOTIFICATION-TYPE
        OBJECTS {
                rbTrapSeqNumber,
                rbTrapSource,
                rbTrapSeverity,
                rbTrapCategory,
                rbSuTxPower
                }
	    STATUS current
	    DESCRIPTION	"SU reached the maximum allowed output power,
	           	rbTrapSource = 	SU
	        	rbTrapSeverity = Info,
				rbTrapCategory = PROC "
        ::= { rbNotifications 81 }

    rbSuMinTxPowerReached    NOTIFICATION-TYPE
        OBJECTS {
                rbTrapSeqNumber,
                rbTrapSource,
                rbTrapSeverity,
                rbTrapCategory,
                rbSuTxPower
                }
   	    STATUS current
	    DESCRIPTION	"SU reached the minimum allowed output power
	           	rbTrapSource = 	SU
	        	rbTrapSeverity = Info,
				rbTrapCategory = PROC "
        ::= { rbNotifications 82 }

    rbSuNetworkEntryStatus    NOTIFICATION-TYPE
        OBJECTS {
                rbTrapSeqNumber,
                rbTrapSource,
                rbTrapSeverity,
                rbTrapCategory,
				rbTrapAdditionalInfo
                }
	    STATUS current
	    DESCRIPTION	"Status of the SU's network entry.
	           	rbTrapSource = 	SU,
	        	rbTrapSeverity = Info,
				rbTrapCategory = PROC,
				rbTrapAdditionalInfo = 132-134"
        ::= { rbNotifications 83 }

    rbSuLicense    NOTIFICATION-TYPE
        OBJECTS {
                rbTrapSeqNumber,
                rbTrapSource,
                rbTrapSeverity,
                rbTrapCategory,
				rbTrapAdditionalInfo,
				rbLicenseId
                }
	    STATUS current
	    DESCRIPTION	"License Grace Period expiration warning,
				rbTrapSource = 	SU
	    		rbTrapSeverity = Info,
				rbTrapCategory = Proc,
				rbTrapAdditionalInfo = 182-186,
				rbLicenseId = Type of License."
        ::= { rbNotifications 84 }

    rbSuDuplicateName    NOTIFICATION-TYPE
        OBJECTS {
                rbTrapSeqNumber,
                rbTrapSource,
                rbTrapSeverity,
                rbTrapCategory,
				rbSuMacAddr,
				rbSuSysName,
				rbSuSysName
                }
	    STATUS current
	    DESCRIPTION	"The SU Name is already in use by another SU.
	                 Services to the SU will be denied until another, unique name is configured for the SU.
	           	rbTrapSource = 	SU,
	        	rbTrapSeverity = Major,
				rbTrapCategory = PROC
				rbSuMacAddr = Mac of other SU with same name,
				rbSuSysName = previous name,
				rbSuSysName = new name"
        ::= { rbNotifications 85 }


--========================================================================
--	Software Download Related Traps		 101..108
--========================================================================

    rbSwDownloadStart    NOTIFICATION-TYPE
        OBJECTS {
                rbTrapSeqNumber,
                rbTrapSource,
                rbTrapSeverity,
                rbTrapCategory
                }
	    STATUS current
	    DESCRIPTION	"Software download process is started.
	        	rbTrapSource = 	NPU/AU/SU
	        	rbTrapSeverity = Info,
				rbTrapCategory = PROC "
        ::= { rbNotifications 101 }

    rbSwDownloadEnd    NOTIFICATION-TYPE
        OBJECTS {
                rbTrapSeqNumber,
                rbTrapSource,
                rbTrapSeverity,
                rbTrapCategory
                }
	    STATUS current
	    DESCRIPTION	"Software download process is finished
				rbTrapSource = 	NPU/AU/SU
	    		rbTrapSeverity = Info,
				rbTrapCategory = PROC "
        ::= { rbNotifications 102 }

    rbSwDownloadError    NOTIFICATION-TYPE
        OBJECTS {
                rbTrapSeqNumber,
                rbTrapSource,
                rbTrapSeverity,
                rbTrapCategory,
                rbTrapAdditionalInfo
                }
	    STATUS current
	    DESCRIPTION	"Software download process error.
				rbTrapSource = 	NPU/AU/SU
				rbTrapSeverity = Minor,
				rbTrapCategory = PROC
				rbTrapAdditionalInfo =100..103"
        ::= { rbNotifications 103 }

    rbSwSwitchFailed    NOTIFICATION-TYPE
        OBJECTS {
                rbTrapSeqNumber,
                rbTrapSource,
                rbTrapSeverity,
                rbTrapCategory,
                rbTrapAdditionalInfo
                }
	    STATUS current
	    DESCRIPTION	"Software switch over failed.
				rbTrapSource = 	NPU/AU/SU
	    		rbTrapSeverity = Minor,
				rbTrapCategory = PROC,
				rbTrapAdditionalInfo = 104..105"
        ::= { rbNotifications 104 }

    rbSwSwitchSucceed    NOTIFICATION-TYPE
        OBJECTS {
                rbTrapSeqNumber,
                rbTrapSource,
                rbTrapSeverity,
                rbTrapCategory,
				rbTrapAdditionalInfo
                }
	    STATUS current
	    DESCRIPTION	"Software switch over succeeded ,
				rbTrapSource = 	NPU/AU/SU
	    		rbTrapSeverity = Info,
				rbTrapCategory = PROC,
				rbTrapAdditionalInfo =  "
        ::= { rbNotifications 105 }

    rbBERTestFinished    NOTIFICATION-TYPE
        OBJECTS {
                rbTrapSeqNumber,
                rbTrapSource,
                rbTrapSeverity,
                rbTrapCategory
                }
	    STATUS current
	    DESCRIPTION	"BER Test is finished ,
				rbTrapSource = 	SU
	    		rbTrapSeverity = Info,
				rbTrapCategory = PROC "
        ::= { rbNotifications 106 }

    rbBERTestStarted    NOTIFICATION-TYPE
        OBJECTS {
                rbTrapSeqNumber,
                rbTrapSource,
                rbTrapSeverity,
                rbTrapCategory
                }
	    STATUS current
	    DESCRIPTION	"BER Test is started ,
				rbTrapSource = 	SU
	    		rbTrapSeverity = Info,
				rbTrapCategory = PROC "
        ::= { rbNotifications 107 }

    rbSwFileConflict    NOTIFICATION-TYPE
        OBJECTS {
                rbTrapSeqNumber,
                rbTrapSource,
                rbTrapSeverity,
                rbTrapCategory
                }
	    STATUS current
	    DESCRIPTION	"AU configured SW file and AU HW mismatch,
				rbTrapSource = 	AU/SU
	    		rbTrapSeverity = Minor,
				rbTrapCategory = PROC "
        ::= { rbNotifications 108 }


--========================================================================
--	Download Related Traps		 109..110
--========================================================================

    rbXMLDownloadResult    NOTIFICATION-TYPE
        OBJECTS {
                rbTrapSeqNumber,
                rbTrapSource,
                rbTrapSeverity,
                rbTrapCategory,
                rbTrapAdditionalInfo
                }
	    STATUS current
	    DESCRIPTION	"XML File Download status.
	        	rbTrapSource = 	NPU
	        	rbTrapSeverity = Info,
				rbTrapCategory = PROC,
				rbTrapAdditionalInfo = 220..224"
        ::= { rbNotifications 109 }

    rbFreqBandDownloadResult    NOTIFICATION-TYPE
        OBJECTS {
                rbTrapSeqNumber,
                rbTrapSource,
                rbTrapSeverity,
                rbTrapCategory,
                rbTrapAdditionalInfo
                }
	    STATUS current
	    DESCRIPTION	"Frequency Band File Download status.
	        	rbTrapSource = 	NPU
	        	rbTrapSeverity = Info,
				rbTrapCategory = PROC,
				rbTrapAdditionalInfo = 220..222,224"
        ::= { rbNotifications 110 }


--========================================================================
--	Service Related Traps				111..115
--========================================================================

    rbServiceDown    NOTIFICATION-TYPE
        OBJECTS {
                rbTrapSeqNumber,
                rbTrapSource,
                rbTrapSeverity,
                rbTrapCategory,
				rbServiceIdx,
				rbSubscriberIdx,
				rbServiceName,
				rbSubscriberID
                }
	    STATUS current
	    DESCRIPTION	"The Service is down or didn't start,
				rbTrapSource = NPU,
	    		rbTrapSeverity = Major,
				rbTrapCategory = QoS"
        ::= { rbNotifications 111 }

    rbServiceUp    NOTIFICATION-TYPE
        OBJECTS {
                rbTrapSeqNumber,
                rbTrapSource,
                rbTrapSeverity,
                rbTrapCategory,
				rbServiceIdx,
				rbSubscriberIdx,
				rbServiceName,
				rbSubscriberID
                }
	    STATUS current
	    DESCRIPTION	"The Service is operational,
				rbTrapSource = NPU,
	    		rbTrapSeverity = Info,
				rbTrapCategory = QoS"
        ::= { rbNotifications 112 }

    rbServiceChanged    NOTIFICATION-TYPE
        OBJECTS {
                rbTrapSeqNumber,
                rbTrapSource,
                rbTrapSeverity,
                rbTrapCategory,
				rbTrapAdditionalInfo,
				rbServiceIdx,
				rbSubscriberIdx,
				rbServiceName,
				rbSubscriberID
                }
	    STATUS current
	    DESCRIPTION	"The Service was modified,
				rbTrapSource = NPU,
	    		rbTrapSeverity = Info,
				rbTrapCategory = QoS,
				rbTrapAdditionalInfo = 119..122"
        ::= { rbNotifications 113 }

    rbServiceGeneralError    NOTIFICATION-TYPE
        OBJECTS {
                rbTrapSeqNumber,
                rbTrapSource,
                rbTrapSeverity,
                rbTrapCategory,
                rbTrapAdditionalInfo,
				rbServiceIdx,
				rbSubscriberIdx,
				rbServiceName,
				rbSubscriberID
                }
	    STATUS current
	    DESCRIPTION	"Service error was detected,
				rbTrapSource = NPU,
	    		rbTrapSeverity = Minor,
				rbTrapCategory = QoS
				rbTrapAdditionalInfo =111..118."
        ::= { rbNotifications 114 }

    rbNetworkingError    NOTIFICATION-TYPE
        OBJECTS {
                rbTrapSeqNumber,
                rbTrapSource,
                rbTrapSeverity,
                rbTrapCategory,
                rbTrapAdditionalInfo
                }
	    STATUS current
	    DESCRIPTION	"Loop was detected on SU Ethernet port,
				rbTrapSource = 	SU
	    		rbTrapSeverity = Info,
				rbTrapCategory = PROC,
				rbTrapAdditionalInfo = 10.. "
         ::= { rbNotifications 115 }


--========================================================================
--	Radius Related Traps				117..127
--========================================================================

    rbSwitchedAuthenticationServer    NOTIFICATION-TYPE
        OBJECTS {
                rbTrapSeqNumber,
                rbTrapSource,
                rbTrapSeverity,
                rbTrapCategory
                }
	    STATUS current
	    DESCRIPTION	"RADIUS Client switched to another Authentication Server,
				rbTrapSource = 	NPU
	    		rbTrapSeverity = Info,
				rbTrapCategory = COMM "
         ::= { rbNotifications 117 }

    rbSwitchedAccountingServer    NOTIFICATION-TYPE
        OBJECTS {
                rbTrapSeqNumber,
                rbTrapSource,
                rbTrapSeverity,
                rbTrapCategory
                }
	    STATUS current
            DESCRIPTION	"RADIUS Client switched to another Accounting Server,
				rbTrapSource = 	NPU
	    		rbTrapSeverity = Info,
				rbTrapCategory = COMM  "
         ::= { rbNotifications 118 }

    rbServiceEstablishmentFailure    NOTIFICATION-TYPE
        OBJECTS {
                rbTrapSeqNumber,
                rbTrapSource,
                rbTrapSeverity,
                rbTrapCategory,
                rbTrapAdditionalInfo,
				rbServiceIdx,
				rbServiceName
                }
	    STATUS current
            DESCRIPTION	"Service establishment failure,
				rbTrapSource = NPU,
	    		rbTrapSeverity = Minor,
				rbTrapCategory = QoS
				rbTrapAdditionalInfo = 200 .. 210, 214
				rbServiceIdx  = Service Profile Idx,
				rbServiceName = Service Name is created from User Name(SU MAC) and Service Pipe index."
         ::= { rbNotifications 119 }

    rbUserAuthenticationTimeout    NOTIFICATION-TYPE
        OBJECTS {
                rbTrapSeqNumber,
                rbTrapSource,
                rbTrapSeverity,
                rbTrapCategory,
                rbTrapAdditionalInfo,
				rbSuMacAddr
                }
	    STATUS current
            DESCRIPTION	"User authentication timeout,
				rbTrapSource = 	NPU
	    		rbTrapSeverity = Info,
				rbTrapCategory = COMM,
				rbTrapAdditionalInfo = 211 .. 213,
				rbSuMacAddr = SU MAC."
         ::= { rbNotifications 120 }

    rbUserAuthenticationReject    NOTIFICATION-TYPE
        OBJECTS {
                rbTrapSeqNumber,
                rbTrapSource,
                rbTrapSeverity,
                rbTrapCategory,
				rbSuMacAddr
                }
	    STATUS current
	    DESCRIPTION	"User authentication rejected,
				rbTrapSource = 	NPU
	    		rbTrapSeverity = Info,
				rbTrapCategory = COMM,
				rbSuMacAddr = SU MAC."
         ::= { rbNotifications 121 }

    rbAuthenticationServerKeepAliveTimeoutOn    NOTIFICATION-TYPE
        OBJECTS {
                rbTrapSeqNumber,
                rbTrapSource,
                rbTrapSeverity,
                rbTrapCategory,
                rbRadiusAuthServerAddress
                }
	    STATUS current
	    DESCRIPTION	"Authentication Server Keep Alive Timeout was detected,
				rbTrapSource = 	NPU,
	    		rbTrapSeverity = Major,
				rbTrapCategory = Equipment,
				rbRadiusAuthServerAddress = Server IP Address."
         ::= { rbNotifications 122 }

    rbAuthenticationServerKeepAliveTimeoutOff    NOTIFICATION-TYPE
        OBJECTS {
                rbTrapSeqNumber,
                rbTrapSource,
                rbTrapSeverity,
                rbTrapCategory,
                rbRadiusAuthServerAddress
                }
	    STATUS current
	    DESCRIPTION	"Previously detected Authentication Server Keep Alive Timeout terminated,
				rbTrapSource = 	NPU,
	    		rbTrapSeverity = Info,
				rbTrapCategory = Equipment,
				rbRadiusAuthServerAddress = Server IP Address."
         ::= { rbNotifications 123 }

    rbAccountingServerKeepAliveTimeoutOn    NOTIFICATION-TYPE
        OBJECTS {
                rbTrapSeqNumber,
                rbTrapSource,
                rbTrapSeverity,
                rbTrapCategory,
                rbRadiusAcctServerAddress
                }
	    STATUS current
	    DESCRIPTION	"Accounting Server Keep Alive Timeout was detected,
				rbTrapSource = 	NPU,
	    		rbTrapSeverity = Major,
				rbTrapCategory = Equipment,
				rbRadiusAcctServerAddress = Server IP Address."
         ::= { rbNotifications 124 }

    rbAccountingServerKeepAliveTimeoutOff    NOTIFICATION-TYPE
        OBJECTS {
                rbTrapSeqNumber,
                rbTrapSource,
                rbTrapSeverity,
                rbTrapCategory,
                rbRadiusAcctServerAddress
                }
	    STATUS current
	    DESCRIPTION	"Previously detected Accounting Server Keep Alive Timeout terminated,
				rbTrapSource = 	NPU,
	    		rbTrapSeverity = Info,
				rbTrapCategory = Equipment,
				rbRadiusAcctServerAddress = Server IP Address."
         ::= { rbNotifications 125 }


--========================================================================
--   GPS Related Traps		   134 .. 160
--========================================================================

    rbExternal1PPSFailureOn    NOTIFICATION-TYPE
        OBJECTS {
                rbTrapSeqNumber,
                rbTrapSource,
                rbTrapSeverity,
                rbTrapCategory
                }
	    STATUS current
	    DESCRIPTION	"External 1PPS failure was detected.
	            BS will produce this alarm only if external 1PPS clock is enabled,
				rbTrapSource = 	NPU,
	    		rbTrapSeverity = Major,
				rbTrapCategory = Equipment."
         ::= { rbNotifications 134 }

    rbExternal1PPSFailureOff    NOTIFICATION-TYPE
        OBJECTS {
                rbTrapSeqNumber,
                rbTrapSource,
                rbTrapSeverity,
                rbTrapCategory
                }
	    STATUS current
	    DESCRIPTION	"Previously detected External 1PPS failure terminated,
				rbTrapSource = 	NPU,
	    		rbTrapSeverity = Info,
				rbTrapCategory = Equipment."
         ::= { rbNotifications 135 }

    rbInternal1PPSFailureOn    NOTIFICATION-TYPE
        OBJECTS {
                rbTrapSeqNumber,
                rbTrapSource,
                rbTrapSeverity,
                rbTrapCategory
                }
	    STATUS current
	    DESCRIPTION	"Internal NPU 1PPS failure was detected,
				rbTrapSource = 	NPU,
	    		rbTrapSeverity = Major,
				rbTrapCategory = Equipment."
         ::= { rbNotifications 136 }

    rbInternal1PPSFailureOff    NOTIFICATION-TYPE
        OBJECTS {
                rbTrapSeqNumber,
                rbTrapSource,
                rbTrapSeverity,
                rbTrapCategory
                }
	    STATUS current
	    DESCRIPTION	"Internal NPU 1PPS failure terminated,
				rbTrapSource = 	NPU,
	    		rbTrapSeverity = Info,
				rbTrapCategory = Equipment."
         ::= { rbNotifications 137 }

    rbExternal16MHzFailureOn    NOTIFICATION-TYPE
        OBJECTS {
                rbTrapSeqNumber,
                rbTrapSource,
                rbTrapSeverity,
                rbTrapCategory
                }
	    STATUS current
	    DESCRIPTION	"External 16MHz failure was detected.
	            BS will produce this alarm only if external 16MHz clock is enabled,
				rbTrapSource = 	NPU,
	    		rbTrapSeverity = Major,
				rbTrapCategory = Equipment."
         ::= { rbNotifications 138 }

    rbExternal16MHzFailureOff    NOTIFICATION-TYPE
        OBJECTS {
                rbTrapSeqNumber,
                rbTrapSource,
                rbTrapSeverity,
                rbTrapCategory
                }
	    STATUS current
	    DESCRIPTION	"External 16MHz failure terminated,
				rbTrapSource = 	NPU,
	    		rbTrapSeverity = Info,
				rbTrapCategory = Equipment."
         ::= { rbNotifications 139 }

    rbInternal16MHzFailureOn    NOTIFICATION-TYPE
        OBJECTS {
                rbTrapSeqNumber,
                rbTrapSource,
                rbTrapSeverity,
                rbTrapCategory
                }
	    STATUS current
	    DESCRIPTION	"Internal NPU 16MHz failure was detected. Can be produced by all types of BSs,
				rbTrapSource = 	NPU,
	    		rbTrapSeverity = Major,
				rbTrapCategory = Equipment."
         ::= { rbNotifications 140 }

    rbInternal16MHzFailureOff    NOTIFICATION-TYPE
        OBJECTS {
                rbTrapSeqNumber,
                rbTrapSource,
                rbTrapSeverity,
                rbTrapCategory
                }
	    STATUS current
	    DESCRIPTION	"Internal NPU 16MHz failure terminated,
				rbTrapSource = 	NPU,
	    		rbTrapSeverity = Info,
				rbTrapCategory = Equipment."
         ::= { rbNotifications 141 }

    rbGPSComFailureOn    NOTIFICATION-TYPE
        OBJECTS {
                rbTrapSeqNumber,
                rbTrapSource,
                rbTrapSeverity,
                rbTrapCategory
                }
	    STATUS current
	    DESCRIPTION	"GPS Com failure was detected. Can be produced only if GPS type is Trimble,
				rbTrapSource = 	NPU,
	    		rbTrapSeverity = Major,
				rbTrapCategory = Equipment."
         ::= { rbNotifications 142 }

    rbGPSComFailureOff    NOTIFICATION-TYPE
        OBJECTS {
                rbTrapSeqNumber,
                rbTrapSource,
                rbTrapSeverity,
                rbTrapCategory
                }
	    STATUS current
	    DESCRIPTION	"GPS Com failure terminated,
				rbTrapSource = 	NPU,
	    		rbTrapSeverity = Info,
				rbTrapCategory = Equipment."
         ::= { rbNotifications 143 }

    rbGPSHealthyFailureOn    NOTIFICATION-TYPE
        OBJECTS {
                rbTrapSeqNumber,
                rbTrapSource,
                rbTrapSeverity,
                rbTrapCategory
                }
	    STATUS current
	    DESCRIPTION	"GPS Healthy failure was detected. Can be produced only if GPS type is Trimble,
				rbTrapSource = 	NPU,
	    		rbTrapSeverity = Major,
				rbTrapCategory = Equipment."
         ::= { rbNotifications 144 }

    rbGPSHealthyFailureOff    NOTIFICATION-TYPE
        OBJECTS {
                rbTrapSeqNumber,
                rbTrapSource,
                rbTrapSeverity,
                rbTrapCategory
                }
	    STATUS current
	    DESCRIPTION	"GPS Healthy failure terminated,
				rbTrapSource = 	NPU,
	    		rbTrapSeverity = Info,
				rbTrapCategory = Equipment."
         ::= { rbNotifications 145 }

    rbMin4SatSyncFailureOn    NOTIFICATION-TYPE
        OBJECTS {
                rbTrapSeqNumber,
                rbTrapSource,
                rbTrapSeverity,
                rbTrapCategory
                }
	    STATUS current
	    DESCRIPTION	"Min4SatSync failure was detected.
	            This indicated that less than four satellites are received by the GPS.
	            Can be produced only if GPS type is Trimble,
				rbTrapSource = 	NPU,
	    		rbTrapSeverity = Major,
				rbTrapCategory = Equipment."
         ::= { rbNotifications 146 }

    rbMin4SatSyncFailureOff    NOTIFICATION-TYPE
        OBJECTS {
                rbTrapSeqNumber,
                rbTrapSource,
                rbTrapSeverity,
                rbTrapCategory
                }
	    STATUS current
	    DESCRIPTION	"Min4SatSync failure terminated,
				rbTrapSource = 	NPU,
	    		rbTrapSeverity = Info,
				rbTrapCategory = Equipment."
         ::= { rbNotifications 147 }

    rbAUExternal1PPSFailureOn    NOTIFICATION-TYPE
        OBJECTS {
                rbTrapSeqNumber,
                rbTrapSource,
                rbTrapSeverity,
                rbTrapCategory
                }
	    STATUS current
	    DESCRIPTION	"External 1PPS failure was detected.
	            Can be produced by AU when the selected 1PPS arriving from active NPU is failed,
				rbTrapSource = 	AU,
	    		rbTrapSeverity = Major,
				rbTrapCategory = Equipment."
         ::= { rbNotifications 148 }

    rbAUExternal1PPSFailureOff    NOTIFICATION-TYPE
        OBJECTS {
                rbTrapSeqNumber,
                rbTrapSource,
                rbTrapSeverity,
                rbTrapCategory
                }
	    STATUS current
	    DESCRIPTION	"External 1PPS failure terminated,
				rbTrapSource = 	AU,
	    		rbTrapSeverity = Info,
				rbTrapCategory = Equipment."
         ::= { rbNotifications 149 }

    rbAUHoldOverEnteredOn    NOTIFICATION-TYPE
        OBJECTS {
                rbTrapSeqNumber,
                rbTrapSource,
                rbTrapSeverity,
                rbTrapCategory
                }
	    STATUS current
	    DESCRIPTION	"HoldOver Entered was detected.
                Can be produced by AU when the AU goes to holdover,
				rbTrapSource = 	AU,
	    		rbTrapSeverity = Major,
				rbTrapCategory = Equipment."
         ::= { rbNotifications 150 }

    rbAUHoldOverEnteredOff    NOTIFICATION-TYPE
        OBJECTS {
                rbTrapSeqNumber,
                rbTrapSource,
                rbTrapSeverity,
                rbTrapCategory
                }
	    STATUS current
	    DESCRIPTION	"HoldOver Entered terminated,
				rbTrapSource = 	AU,
	    		rbTrapSeverity = Info,
				rbTrapCategory = Equipment."
         ::= { rbNotifications 151 }

    rbAUHoldOverTimeoutPassedOn    NOTIFICATION-TYPE
        OBJECTS {
                rbTrapSeqNumber,
                rbTrapSource,
                rbTrapSeverity,
                rbTrapCategory
                }
	    STATUS current
	    DESCRIPTION	"HoldOver passed was detected.
                Can be produced by AU when the AU holdover passed the Timeout,
				rbTrapSource = 	AU,
	    		rbTrapSeverity = Major,
				rbTrapCategory = Equipment."
         ::= { rbNotifications 152 }

    rbAUHoldOverTimeoutPassedOff    NOTIFICATION-TYPE
        OBJECTS {
                rbTrapSeqNumber,
                rbTrapSource,
                rbTrapSeverity,
                rbTrapCategory
                }
	    STATUS current
	    DESCRIPTION	"HoldOver passed terminated,
				rbTrapSource = 	AU,
	    		rbTrapSeverity = Info,
				rbTrapCategory = Equipment."
         ::= { rbNotifications 153 }

    rbAUHoldOverTxStoppedOn    NOTIFICATION-TYPE
        OBJECTS {
                rbTrapSeqNumber,
                rbTrapSource,
                rbTrapSeverity,
                rbTrapCategory
                }
	    STATUS current
	    DESCRIPTION	"HoldOver passed and Stop TX operation was detected,
				rbTrapSource = 	AU,
				rbTrapSeverity = Major,
				rbTrapCategory = Equipment."
         ::= { rbNotifications 154 }

    rbAUHoldOverTxStoppedOff    NOTIFICATION-TYPE
        OBJECTS {
                rbTrapSeqNumber,
                rbTrapSource,
                rbTrapSeverity,
                rbTrapCategory
                }
	    STATUS current
	    DESCRIPTION	"Stop TX operation terminated,
				rbTrapSource = 	AU,
				rbTrapSeverity = Info,
				rbTrapCategory = Equipment."
         ::= { rbNotifications 155 }


END
