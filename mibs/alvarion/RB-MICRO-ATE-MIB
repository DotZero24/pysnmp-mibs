--
--
--                  Rainbow Management Ate MIB
--
--                         03/03/06
--
--
--      =================================

RB-MICRO-ATE-MIB	DEFINITIONS ::= BEGIN
	IMPORTS
		DisplayString
			FROM SNMPv2-TC
		MODULE-IDENTITY, OBJECT-TYPE, enterprises, Integer32
			FROM SNMPv2-SMI;


	rainbowMicroBSTAteMib	MODULE-IDENTITY
		LAST-UPDATED	"200603031500Z"
		ORGANIZATION	"Alvarion Ltd."
		CONTACT-INFO	"Alvarion Customer Service
		Postal: Alvarion Ltd.
			Barzel 21
			Tel Aviv 69710
			ISRAEL
               	E-mail: CS_Coordinator@alvarion.com"
		DESCRIPTION
				"Rainbow Micro-BST ATE"
		REVISION		"200603031500Z"
		DESCRIPTION
				"Revision 2.1"
		::=  {  rainbow  302  }


	alvarion	OBJECT IDENTIFIER
		::=  {  enterprises  12394  }

	products	OBJECT IDENTIFIER
		::=  {  alvarion  1  }

	rainbow	OBJECT IDENTIFIER
		::=  {  products  2  }


-- ===========================================================================
-- System ATE Parameters
-- ===========================================================================
	rbAteMicroConfig    	OBJECT IDENTIFIER		::=  {  rainbowMicroBSTAteMib  1  }
	rbAteMicroClockConfig  	OBJECT IDENTIFIER		::=  {  rainbowMicroBSTAteMib  2  }
	rbAteMicroTestResults  	OBJECT IDENTIFIER		::=  {  rainbowMicroBSTAteMib  3  }
	rbAteMicroBurnFuncs    	OBJECT IDENTIFIER		::=  {  rainbowMicroBSTAteMib  4  }
	rbAteMicroCleanUpParams	OBJECT IDENTIFIER		::=  {  rainbowMicroBSTAteMib  5  }
	rbAteManualTests    	OBJECT IDENTIFIER		::=  {  rainbowMicroBSTAteMib  6  }


-- ===========================================================================
-- System ATE Config Parameters
-- ===========================================================================

 	rbAteMicroStartTest	OBJECT-TYPE
		SYNTAX			INTEGER  {
		                           none ( 1 ) ,
		                           startFullTest ( 2 ),
		                           startHostTest ( 3 ),
		                           startPhysicalTest ( 4 ),
								   startMonitorTest ( 5 ),
								   startWatchDogTest ( 6 )
		                         }
		MAX-ACCESS		read-write
		STATUS			current
		DESCRIPTION
				"To start ATE test perform SET with startFullTest (The NPU will reset and start Full test in ATE mode).
				When startHostTest the NPU will Start the only the host test (no reset), startPhysicalTest will cause
				a reset and start physiacl test only. startMonitorTest performs monitor test only"
		::=  {  rbAteMicroConfig  1  }

 	rbAteMicroTimeToRunPhysicalTest	OBJECT-TYPE
		SYNTAX			Integer32
		MAX-ACCESS		read-write
		STATUS			current
		DESCRIPTION
				"Time to run Physical test"
		::=  {  rbAteMicroConfig  2  }

 	rbAteMicroNumOfPacketsToRunPhysTest	OBJECT-TYPE
		SYNTAX			Integer32
		MAX-ACCESS		read-write
		STATUS			current
		DESCRIPTION
				"Number of Packets to run in Physical test"
		::=  {  rbAteMicroConfig  3  }

 	rbAteMicroTestStatus	OBJECT-TYPE
		SYNTAX			INTEGER  {
		                           readyForTest ( 1 ) ,
		                           testInProgress ( 2 )
		                         }
		MAX-ACCESS		read-only
		STATUS			current
		DESCRIPTION
				"readyForTest - any test can be started."
		::=  {  rbAteMicroConfig  4  }

 	rbAteSnmpRelaySupport	OBJECT-TYPE
		SYNTAX			INTEGER  { unknown ( 0 ) ,
		                           relayOn ( 1 ) ,
		                           relayOff ( 2 )
		                         }
		MAX-ACCESS		read-write
		STATUS			current
		DESCRIPTION
				"rbAteSnmpRelaySupport - relay SNMP messages to AU/SU ON/OFF.
				 Relaying is done according to community:
				 @ATE@@AU.x = relay to AU in slot x.
				 @ATE@@SU.xx-xx-xx-xx-xx-xx = relay to SU with MAC xx-xx-xx-xx-xx-xx."
		::=  {  rbAteMicroConfig  5  }


-- ===========================================================================
-- System ATE Clock Setting Parameters
-- ===========================================================================

 	rbAteMicroDateDay	OBJECT-TYPE
		SYNTAX			Integer32
		MAX-ACCESS		read-write
		STATUS			current
		DESCRIPTION
				"For reading or setting the date"
		::=  {  rbAteMicroClockConfig  1  }

 	rbAteMicroDateDayOfWeek	OBJECT-TYPE
		SYNTAX			INTEGER  {
		                           monday ( 1 ) ,
		                           tuesday ( 2 ) ,
		                           wednesday ( 3 ) ,
		                           thursday ( 4 ) ,
		                           friday ( 5 ) ,
		                           saturday ( 6 ) ,
		                           sunday ( 7 )
		                         }
		MAX-ACCESS		read-write
		STATUS			current
		DESCRIPTION
				"For reading or setting the date"
		::=  {  rbAteMicroClockConfig  2  }

 	rbAteMicroDateMonth	OBJECT-TYPE
		SYNTAX			Integer32
		MAX-ACCESS		read-write
		STATUS			current
		DESCRIPTION
				"For reading or setting the date"
		::=  {  rbAteMicroClockConfig  3  }

 	rbAteMicroDateYear	OBJECT-TYPE
		SYNTAX			Integer32
		MAX-ACCESS		read-write
		STATUS			current
		DESCRIPTION
				"For reading or setting the date"
		::=  {  rbAteMicroClockConfig  4  }

 	rbAteMicroDateHour	OBJECT-TYPE
		SYNTAX			Integer32
		MAX-ACCESS		read-write
		STATUS			current
		DESCRIPTION
				"For reading or setting the time of day"
		::=  {  rbAteMicroClockConfig  5  }

 	rbAteMicroDateMin	OBJECT-TYPE
		SYNTAX			Integer32
		MAX-ACCESS		read-write
		STATUS			current
		DESCRIPTION
				"For reading or setting the time of day"
		::=  {  rbAteMicroClockConfig  6  }

 	rbAteMicroDateSec	OBJECT-TYPE
		SYNTAX			Integer32
		MAX-ACCESS		read-write
		STATUS			current
		DESCRIPTION
				"For reading or setting the time of day"
		::=  {  rbAteMicroClockConfig  7  }


-- ===========================================================================
-- System ATE Result Parameters
-- ===========================================================================

	rbAteMicroTestResultsConfig	OBJECT IDENTIFIER		::=  {  rbAteMicroTestResults  1  }
	rbAteMicroTestResultsTab  	OBJECT IDENTIFIER		::=  {  rbAteMicroTestResults  2  }

 	rbAteMicroSaveTestResultsToFlash	OBJECT-TYPE
		SYNTAX			INTEGER  {
		                           doNothing ( 1 ) ,
		                           saveResults ( 2 )
		                         }
		MAX-ACCESS		read-write
		STATUS			current
		DESCRIPTION
				"The NPU will save last test results to flash"
		::=  {  rbAteMicroTestResultsConfig  1  }

 	rbAteMicroRecallTestResultsFromFlash	OBJECT-TYPE
		SYNTAX			INTEGER  {
		                           doNothing ( 1 ) ,
		                           recallResults ( 2 )
		                         }
		MAX-ACCESS		read-write
		STATUS			current
		DESCRIPTION
				"The NPU will recall test results from flash into Memory"
		::=  {  rbAteMicroTestResultsConfig  2  }

	rbAteMicroTestResultsTable	OBJECT-TYPE
		SYNTAX		SEQUENCE  OF  RbAteMicroTestResultsEntry
		MAX-ACCESS	not-accessible
		STATUS		current
		DESCRIPTION
			"Table to get all Test Results"
		::=  { rbAteMicroTestResultsTab  1 }

	rbAteMicroTestResultsEntry	OBJECT-TYPE
		SYNTAX		RbAteMicroTestResultsEntry
		MAX-ACCESS	not-accessible
		STATUS		current
		DESCRIPTION
			"Row Description"
		INDEX		{  rbAteMicroTestType  }
		::=  { rbAteMicroTestResultsTable 1 }

	RbAteMicroTestResultsEntry  ::=  SEQUENCE {
		rbAteMicroTestType               INTEGER,
		rbAteMicroTestResult             INTEGER,
		rbAteMicroTestResultVal          Integer32,
		rbAteMicroTestResultDescription  DisplayString
		}

 	rbAteMicroTestType	OBJECT-TYPE
		SYNTAX			INTEGER  {
		                           flashMemoryTest ( 1 ) ,
		                           sdRAMMemoryTest ( 2 ) ,
		                           watchDogTest ( 3 ) ,
		                           diskOnChipMemoryTest ( 4 ) ,
		                           tempSensorTest ( 5 ) ,
		                           i2CBusIntTest ( 6 ) ,
		                           rs232MonitorTest ( 7 ) ,
		                           alarmsInOutTest ( 8 ) ,
		                           acmInOutTest ( 9 ) ,
		                           mngEthernetPortTest ( 10 ) ,
		                           dataEthernetPortTest ( 11 ) ,
		                           backPlaneEthernetPortTest ( 12 ) ,
		                           gpsTest ( 13 ) ,
		                           bstSyncTest ( 14 ) ,
		                           test16mhzAnd1pps ( 15 )
		                         }
		MAX-ACCESS		read-only
		STATUS			current
		DESCRIPTION
				"Type Of Test"
		::=  {  rbAteMicroTestResultsEntry  1  }

 	rbAteMicroTestResult	OBJECT-TYPE
		SYNTAX			INTEGER  {
		                           success ( 0 ) ,
		                           failed ( 1 ) ,
		                           inactive ( 2 ) ,
		                           notChecked ( 3 )
		                         }
		MAX-ACCESS		read-only
		STATUS			current
		DESCRIPTION
				"Last Test Result!"
		::=  {  rbAteMicroTestResultsEntry  2  }

 	rbAteMicroTestResultVal	OBJECT-TYPE
		SYNTAX			Integer32
		MAX-ACCESS		read-only
		STATUS			current
		DESCRIPTION
				"Last Test Result Value!"
		::=  {  rbAteMicroTestResultsEntry  3  }

 	rbAteMicroTestResultDescription	OBJECT-TYPE
		SYNTAX			DisplayString (SIZE (1..255))
		MAX-ACCESS		read-only
		STATUS			current
		DESCRIPTION
				"Test Result Description!"
		::=  {  rbAteMicroTestResultsEntry  4  }


-- ===========================================================================
-- System Burn Parameters
-- ===========================================================================

 	rbAteMicroEnterSerialNum	OBJECT-TYPE
		SYNTAX			DisplayString (SIZE (1..32))
		MAX-ACCESS		read-write
		STATUS			current
		DESCRIPTION
				"To start ATE burn functionality! locked after first burn!"
		::=  {  rbAteMicroBurnFuncs  1  }

 	rbAteMicroEnterDataMacAddr	OBJECT-TYPE
		SYNTAX			DisplayString (SIZE (1..12))
		MAX-ACCESS		read-write
		STATUS			current
		DESCRIPTION
				"To start ATE burn functionality! locked after first burn!"
		::=  {  rbAteMicroBurnFuncs  2  }

 	rbAteMicroEnterMngmntMacAddr	OBJECT-TYPE
		SYNTAX			DisplayString (SIZE (1..12))
		MAX-ACCESS		read-write
		STATUS			current
		DESCRIPTION
				"To start ATE burn functionality! locked after first burn!"
		::=  {  rbAteMicroBurnFuncs  3  }

 	rbAteMicroGetIduHwRevision	OBJECT-TYPE
		SYNTAX			DisplayString (SIZE (1..32))
		MAX-ACCESS		read-only
		STATUS			current
		DESCRIPTION
				"To start ATE burn functionality! locked after first burn!"
		::=  {  rbAteMicroBurnFuncs  4  }


-- ===========================================================================
-- ATE Cleanup Params
-- ===========================================================================

 	rbAteMicroDeleteNpuShadowFile	OBJECT-TYPE
		SYNTAX			INTEGER  {
		                           none ( 1 ) ,
		                           delete ( 2 )
		                         }
		MAX-ACCESS		read-write
		STATUS			current
		DESCRIPTION
				"Deletes the existing file name!"
		::=  {  rbAteMicroCleanUpParams  1  }

 	rbAteMicroSetServiceDefault	OBJECT-TYPE
		SYNTAX			INTEGER  {
		                           none ( 1 ) ,
		                           setDefault ( 2 )
		                         }
		MAX-ACCESS		read-write
		STATUS			current
		DESCRIPTION
				"Sets a Services to default and reboots NPU!"
		::=  {  rbAteMicroCleanUpParams  2  }

 	rbAteMicroPowerOnCntReset	OBJECT-TYPE
		SYNTAX			INTEGER  {
		                           none ( 1 ) ,
		                           reset ( 2 )
		                         }
		MAX-ACCESS		read-write
		STATUS			current
		DESCRIPTION
				"Resets the Cumulative Power On Time Counter"
		::=  {  rbAteMicroCleanUpParams  3  }


-- ===========================================================================
-- ATE Manual Tests
-- ===========================================================================

 	rbAteLedTest 	OBJECT-TYPE
		SYNTAX			INTEGER  {
		                           none ( 1 ) ,
		                           startTest ( 2 ) ,
		                           stopTest ( 3 )
		                         }
		MAX-ACCESS		read-write
		STATUS			current
		DESCRIPTION
				"Activates/deactivates LED test!"
		::=  {  rbAteManualTests  1  }


END
