-- ============================================================
-- Description :
--
--                  Rainbow Radius Management Information Base
--
--                         06/06/2006
--
--
-- ============================================================

RAINBOW-RADIUS-MIB	DEFINITIONS ::= BEGIN
	IMPORTS
		rainbow
			FROM RAINBOW-MIB
		RowStatus
			FROM SNMPv2-TC
		MODULE-IDENTITY, OBJECT-TYPE, IpAddress, Integer32
			FROM SNMPv2-SMI;

	rbRadiusClient	MODULE-IDENTITY
		LAST-UPDATED	"200606061500Z"
		ORGANIZATION	"Alvarion Ltd."
		CONTACT-INFO	"Alvarion Customer Service
		Postal: Alvarion Ltd.
			Barzel 21
			Tel Aviv 69710
			ISRAEL
               	E-mail: CS_Coordinator@alvarion.com"
		DESCRIPTION
				"Rainbow RADIUS Client"
		REVISION		"200606061500Z"
		DESCRIPTION
				"Revision 2.5"
		::=  {  rainbow  150  }


--	alvarion	OBJECT IDENTIFIER
--		::=  {  enterprises  12394  }

--	products	OBJECT IDENTIFIER
--		::=  {  alvarion  1  }

--	rainbow	OBJECT IDENTIFIER
--		::=  {  products  2  }



--========================================================================
--     Radius General Parameters
--========================================================================

	rbRadiusClientGeneralParams   OBJECT IDENTIFIER ::= {  rbRadiusClient 1 }

	rbRadiusClientRetryInterval	OBJECT-TYPE
		SYNTAX			Integer32	( 1 .. 5 )
		MAX-ACCESS		read-write
		STATUS			current
		DESCRIPTION
				"The time to wait (in sec) before resending a RADIUS message if no
				 response is received."
	    DEFVAL {5}
		::=  {  rbRadiusClientGeneralParams  2  }

	rbRadiusClientMaxNumOfRetries	OBJECT-TYPE
		SYNTAX			Integer32	( 0 .. 5 )
		MAX-ACCESS		read-write
		STATUS			current
		DESCRIPTION
				"The maximum number of retrials.
				 If the server does not respond after reaching the maximum number
				 of retries, the client should try the next server in the list,
				 if available."
	    DEFVAL {3}
		::=  {  rbRadiusClientGeneralParams  3  }

	rbRadiusClientKeepAliveTimeout	OBJECT-TYPE
		SYNTAX			Integer32  ( 60 .. 180 )
		MAX-ACCESS		read-write
		STATUS			current
		DESCRIPTION
				"The time to wait (in seconds) between keep-alive messages to the RADIUS server.
				 The configurable range is 60 - 180 seconds."
	    DEFVAL {60}
		::=  {  rbRadiusClientGeneralParams  4 }


--========================================================================
--     Radius Authentication Servers
--========================================================================

	rbRadiusAuthServerTable OBJECT-TYPE
	    SYNTAX     SEQUENCE OF RbRadiusAuthServerEntry
	    MAX-ACCESS not-accessible
	    STATUS     current
	    DESCRIPTION
	            "The (conceptual) table listing the parameters of up to 2
	             RADIUS authentication servers."
	    ::= { rbRadiusClient 2 }

	rbRadiusAuthServerEntry OBJECT-TYPE
	    SYNTAX     RbRadiusAuthServerEntry
	    MAX-ACCESS not-accessible
	    STATUS     current
	    DESCRIPTION
	            "An entry (conceptual row) representing a RADIUS authentication server
	             with which the client can communicate."
	    INDEX      { rbRadiusAuthServerAddress }
	    ::= { rbRadiusAuthServerTable 1 }

	RbRadiusAuthServerEntry ::= SEQUENCE {
	    rbRadiusAuthServerAddress            IpAddress,
		rbRadiusAuthServerRowStatus  	     RowStatus,
	    rbRadiusAuthServerIndex              Integer32,
	    rbRadiusAuthServerPortNumber         Integer32,
	    rbRadiusAuthServerType               INTEGER,
	    rbRadiusAuthServerStatus             INTEGER,
	    rbRadiusAuthServerOperStatus         INTEGER,
	    rbRadiusAuthServerResetCounters      INTEGER
	}

	rbRadiusAuthServerAddress OBJECT-TYPE
	    SYNTAX     		IpAddress
	    MAX-ACCESS 		read-only
	    STATUS     		current
	    DESCRIPTION
	            "The IP address of the RADIUS Authentication server
	             referred to in this table entry."
	    ::= { rbRadiusAuthServerEntry 1 }

	rbRadiusAuthServerRowStatus	OBJECT-TYPE
		SYNTAX			RowStatus
		MAX-ACCESS		read-write
		STATUS			current
		DESCRIPTION
				"Control for creating and deleting entries.  Entries may be modified while active.
                 active (1) - means that the entry is available for use by the managed device and relevant parameters
                 may be modified;
                 createAndGo (4) is used for creating a new entry and to have its status automatically set to active;
                 destroy (6) is used for deleting an existing entry."
		::=  {  rbRadiusAuthServerEntry  2  }

	rbRadiusAuthServerIndex OBJECT-TYPE
	    SYNTAX     		Integer32 ( 1 .. 2 )
	    MAX-ACCESS 		read-only
	    STATUS     		current
	    DESCRIPTION
	            "A number uniquely identifying each RADIUS Authentication server
	             with which this client can communicate."
	    ::= { rbRadiusAuthServerEntry 3 }

	rbRadiusAuthServerPortNumber  OBJECT-TYPE
	    SYNTAX 			Integer32 ( 1 .. 65535 )
		MAX-ACCESS		read-write
	    STATUS 			current
	    DESCRIPTION
	            "The UDP port the client is using to send requests to this server."
	    DEFVAL {1812}
	    ::= { rbRadiusAuthServerEntry 4 }

	rbRadiusAuthServerType	OBJECT-TYPE
		SYNTAX			INTEGER { primary   (1),
						          secondary (2) }
		MAX-ACCESS		read-write
		STATUS			current
		DESCRIPTION
				"Defines the type of the Server.
				 Only One Server can be Primary. Primary Server cannont be changed to Secondary."
		::=  {  rbRadiusAuthServerEntry  5  }

	rbRadiusAuthServerStatus	OBJECT-TYPE
		SYNTAX			INTEGER { active  (1),
						          standby (2) }
		MAX-ACCESS		read-only
		STATUS			current
		DESCRIPTION
				"Defines the status of the Server."
		::=  {  rbRadiusAuthServerEntry  6  }

	rbRadiusAuthServerOperStatus	OBJECT-TYPE
		SYNTAX			INTEGER { up   (1),
						          down (2) }
		MAX-ACCESS		read-only
		STATUS			current
		DESCRIPTION
				"RADIUS Authentication server operational status."
		::=  {  rbRadiusAuthServerEntry  7  }

	rbRadiusAuthServerResetCounters   OBJECT-TYPE
		SYNTAX		 	INTEGER	{ noAction (0),
		                          reset    (1) }
		MAX-ACCESS		read-write
		STATUS			current
		DESCRIPTION
				"When set to reset (1), the Radius Authentication server counters will be initialized to 0.
				 noAction (0) value is available to support Get and Get Next commands.
				 It should not be used in Set commands."
		::=  {  rbRadiusAuthServerEntry  8  }


--========================================================================
--     Radius Accounting Servers
--========================================================================

	rbRadiusAccountServerTable OBJECT-TYPE
	    SYNTAX     SEQUENCE OF RbRadiusAccountServerEntry
	    MAX-ACCESS not-accessible
	    STATUS     current
	    DESCRIPTION
	            "The (conceptual) table listing up to 2 RADIUS accounting servers."
	    ::= { rbRadiusClient 3 }

	rbRadiusAccountServerEntry OBJECT-TYPE
	    SYNTAX     RbRadiusAccountServerEntry
	    MAX-ACCESS not-accessible
	    STATUS     current
	    DESCRIPTION
	            "An entry (conceptual row) representing a RADIUS
	             accounting server with which the client can communicate."
	    INDEX      { rbRadiusAcctServerAddress }
	    ::= { rbRadiusAccountServerTable 1 }

	RbRadiusAccountServerEntry ::= SEQUENCE {
	    rbRadiusAcctServerAddress            IpAddress,
		rbRadiusAcctServerRowStatus  		 RowStatus,
	    rbRadiusAcctServerIndex              Integer32,
	    rbRadiusAcctServerPortNumber         Integer32,
	    rbRadiusAcctServerType               INTEGER,
	    rbRadiusAcctServerStatus             INTEGER,
	    rbRadiusAcctServerOperStatus         INTEGER,
	    rbRadiusAcctServerResetCounters      INTEGER
	}

	rbRadiusAcctServerAddress OBJECT-TYPE
	    SYNTAX     		IpAddress
	    MAX-ACCESS 		read-only
	    STATUS     		current
	    DESCRIPTION
	            "The IP address of the RADIUS Accounting server
	             referred to in this table entry."
	    ::= { rbRadiusAccountServerEntry 1 }

	rbRadiusAcctServerRowStatus	OBJECT-TYPE
		SYNTAX			RowStatus
		MAX-ACCESS		read-write
		STATUS			current
		DESCRIPTION
				"Control for creating and deleting entries.  Entries may be modified while active.
                 active (1) - means that the entry is available for use by the managed device and relevant parameters
                 may be modified;
                 createAndGo (4) is used for creating a new entry and to have its status automatically set to active;
                 destroy (6) is used for deleting an existing entry."
		::=  {  rbRadiusAccountServerEntry  2  }

	rbRadiusAcctServerIndex OBJECT-TYPE
	    SYNTAX     		Integer32 ( 1 .. 2 )
	    MAX-ACCESS 		read-only
	    STATUS     		current
	    DESCRIPTION
	            "A number uniquely identifying each RADIUS Accounting server
	             with which this client can communicate."
	    ::= { rbRadiusAccountServerEntry 3 }

	rbRadiusAcctServerPortNumber  OBJECT-TYPE
	    SYNTAX 			Integer32 ( 1 .. 65535 )
		MAX-ACCESS		read-write
	    STATUS 			current
	    DESCRIPTION
	            "The UDP port the client is using to send requests to this server."
	    DEFVAL {1813}
	    ::= { rbRadiusAccountServerEntry 4 }

	rbRadiusAcctServerType	OBJECT-TYPE
		SYNTAX			INTEGER { primary (1),
						          secondary (2) }
		MAX-ACCESS		read-write
		STATUS			current
		DESCRIPTION
				"Defines the type of the Server.
				 Only One Server can be Primary. Primary Server cannont be
				 changed to Secondary."
		::=  {  rbRadiusAccountServerEntry  5  }

	rbRadiusAcctServerStatus	OBJECT-TYPE
		SYNTAX			INTEGER { active  (1),
						          standby (2) }
		MAX-ACCESS		read-only
		STATUS			current
		DESCRIPTION
				"Defines the status of the Server."
		::=  {  rbRadiusAccountServerEntry  6  }

	rbRadiusAcctServerOperStatus	OBJECT-TYPE
		SYNTAX			INTEGER { up   (1),
						          down (2) }
		MAX-ACCESS		read-only
		STATUS			current
		DESCRIPTION
				"RADIUS Accounting server operational status."
		::=  {  rbRadiusAccountServerEntry  7  }

	rbRadiusAcctServerResetCounters   OBJECT-TYPE
		SYNTAX		 	INTEGER	{ noAction (0),
		                          reset    (1) }
		MAX-ACCESS		read-write
		STATUS			current
		DESCRIPTION
				"When set to reset (1), the Radius Accounting server counters will be initialized to 0.
				 noAction (0) value is available to support Get and Get Next commands.
				 It should not be used in Set commands."
		::=  {  rbRadiusAccountServerEntry  8  }


END
