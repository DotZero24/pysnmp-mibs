-- ****************************************************************************
--  ALVARION-802DOT1X-MIB definitions
--
--  Copyright (c) 2007, Alvarion Ltd.
--  All Rights Reserved.
--
--  Alvarion 802.1x Extention MIB file.

--
--
-- ****************************************************************************


ALVARION-802DOT1X-ACCESS-MIB DEFINITIONS ::= BEGIN

IMPORTS
    MODULE-IDENTITY, OBJECT-TYPE,
    Unsigned32
        FROM SNMPv2-SMI
    TruthValue
        FROM SNMPv2-TC
    MODULE-COMPLIANCE, OBJECT-GROUP
        FROM SNMPv2-CONF
    alvarionMgmtV2
        FROM ALVARION-SMI
;


alvarion802Dot1xMIB MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Alvarion 802.1x Extention MIB."

    ::= { alvarionMgmtV2 8 }


-- 802.1x mib definition
coPaeMIBObjects         OBJECT IDENTIFIER ::= { alvarion802Dot1xMIB 1 }

-- Pae groups
coDot1xPaeSystem        OBJECT IDENTIFIER ::= { coPaeMIBObjects 1 }
coDot1xPaeAuthenticator OBJECT IDENTIFIER ::= { coPaeMIBObjects 2 }


-- The alvarion PAE System Group
coDot1xPaeSystemModifyKey OBJECT-TYPE
    SYNTAX      TruthValue
    MAX-ACCESS  read-only
    STATUS      current
    DESCRIPTION "Indicates if WEP and TKIP group keys are updated at
                 regular intervals.
                   'true': Group key update is enabled.
                   'false': Group key update is disabled."
    DEFVAL      { false }
    ::= { coDot1xPaeSystem 1 }

coDot1xPaeSystemModifyKeyInterval OBJECT-TYPE
    SYNTAX      Unsigned32 (30..65535)
    UNITS       "seconds"
    MAX-ACCESS  read-write
    STATUS      current
    DESCRIPTION "Specifies the interval (in seconds) between updates of the WEP transmit keys."
    DEFVAL      { 300 }
    ::= { coDot1xPaeSystem 2 }


-- The alvarion PAE Authenticator Group
coDot1xAuthQuietPeriod OBJECT-TYPE
    SYNTAX      Unsigned32 (0..65535)
    UNITS       "seconds"
    MAX-ACCESS  read-write
    STATUS      current
    DESCRIPTION "Specifies the initial value of the quietPeriod constant used
                 by the Authenticator PAE state machine."
    DEFVAL      { 60 }
    ::= { coDot1xPaeAuthenticator 1 }

coDot1xAuthTxPeriod OBJECT-TYPE
    SYNTAX      Unsigned32 (1..65535)
    UNITS       "seconds"
    MAX-ACCESS  read-write
    STATUS      current
    DESCRIPTION "Specifies the initial value of the txPeriod constant used by
                 the Authenticator PAE state machine."
    DEFVAL      { 30 }
    ::= { coDot1xPaeAuthenticator 2 }

coDot1xAuthSuppTimeout OBJECT-TYPE
    SYNTAX      Unsigned32 (1..65535)
    UNITS       "seconds"
    MAX-ACCESS  read-write
    STATUS      current
    DESCRIPTION "Specifies the initial value of the suppTimeout constant used
                 by the Backend Authentication state machine."
    DEFVAL      { 3 }
    ::= { coDot1xPaeAuthenticator 3 }

coDot1xAuthServerTimeout OBJECT-TYPE
    SYNTAX      Unsigned32 (1..65535)
    UNITS       "seconds"
    MAX-ACCESS  read-write
    STATUS      current
    DESCRIPTION "Specifies the initial value of the serverTimeout constant used
                 by the Backend Authentication state machine."
    DEFVAL      { 30 }
    ::= { coDot1xPaeAuthenticator 4 }

coDot1xAuthMaxReq OBJECT-TYPE
    SYNTAX      Unsigned32 (1..10)
    MAX-ACCESS  read-write
    STATUS      current
    DESCRIPTION "Specifies the initial value of the maxReq constant used by
                 the Backend Authentication state machine."
    DEFVAL      { 2 }
    ::= { coDot1xPaeAuthenticator 5 }

coDot1xAuthReAuthPeriod OBJECT-TYPE
    SYNTAX      Unsigned32 (1..65535)
    UNITS       "seconds"
    MAX-ACCESS  read-write
    STATUS      current
    DESCRIPTION "Specifies the initial value of the reAuthPeriod constant used
                 by the Reauthentication Timer state machine."
    DEFVAL      { 3600 }
    ::= { coDot1xPaeAuthenticator 6 }

coDot1xAuthReAuthEnabled OBJECT-TYPE
    SYNTAX      TruthValue
    MAX-ACCESS  read-write
    STATUS      current
    DESCRIPTION "Specifies the enable/disable control used by the
                 Reauthentication Timer state machine (8.5.5.1).

                   'true': Enables the control used by the
                           re-authentication timer state machine.

                   'false': Disables the control."
    DEFVAL      { false }
    ::= { coDot1xPaeAuthenticator 7 }

coDot1xAuthKeyTxEnabled OBJECT-TYPE
    SYNTAX      TruthValue
    MAX-ACCESS  read-write
    STATUS      current
    DESCRIPTION "Specifies the initial value of the keyTransmissionEnabled
                 constant used by the Authenticator PAE state machine.

                   'true': Enables the constant used by the Authenticator
                           PAE state machine.

                   'false': Disables the constant."
    DEFVAL      { true }
    ::= { coDot1xPaeAuthenticator 8 }

coDot1xAuthReAuthMax OBJECT-TYPE
    SYNTAX      Unsigned32 (1..65535)
    MAX-ACCESS  read-write
    STATUS      current
    DESCRIPTION "Specifies the number of reauthentication attempts that are
                 permitted before the Port becomes Unauthorized."
    DEFVAL      { 8 }
    ::= { coDot1xPaeAuthenticator 9 }


-- ALVARION 802.1X Extension MIB - Conformance Information
coDot1xPaeConformance   OBJECT IDENTIFIER ::= { alvarion802Dot1xMIB 2 }
coDot1xPaeGroups        OBJECT IDENTIFIER ::= { coDot1xPaeConformance 1 }
coDot1xPaeCompliances   OBJECT IDENTIFIER ::= { coDot1xPaeConformance 2 }


-- units of conformance
coDot1xPaeSystemGroup OBJECT-GROUP
    OBJECTS     {
                    coDot1xPaeSystemModifyKey,
                    coDot1xPaeSystemModifyKeyInterval
                }
    STATUS      current
    DESCRIPTION "A collection of objects providing extended system information
                 about, and control over, a PAE."
    ::= { coDot1xPaeGroups 1 }

coDot1xPaeAuthenticatorGroup OBJECT-GROUP
    OBJECTS     {
                    coDot1xAuthQuietPeriod,
                    coDot1xAuthTxPeriod,
                    coDot1xAuthSuppTimeout,
                    coDot1xAuthServerTimeout,
                    coDot1xAuthMaxReq,
                    coDot1xAuthReAuthPeriod,
                    coDot1xAuthReAuthEnabled,
                    coDot1xAuthKeyTxEnabled,
                    coDot1xAuthReAuthMax
                }
    STATUS      current
    DESCRIPTION "A collection of objects providing configuration information
                 about all Authenticator PAE."
    ::= { coDot1xPaeGroups 2 }


-- compliance statements
coDot1xPaeCompliance MODULE-COMPLIANCE
    STATUS      current
    DESCRIPTION "The compliance statement for extended device support of Port
                 Access Control."
    MODULE      MANDATORY-GROUPS
                    {
                        coDot1xPaeSystemGroup,
                        coDot1xPaeAuthenticatorGroup
                    }
    ::= { coDot1xPaeCompliances 1 }

END
