-- ****************************************************************************
--  ALVARION-SATELLITE-MANAGEMENT-MIB definitions
--
--  Copyright (c) 2007, Alvarion Ltd.
--  All Rights Reserved.
--
--  Alvarion Satellite Management MIB file.
--
-- ****************************************************************************


ALVARION-SATELLITE-MANAGEMENT-MIB DEFINITIONS ::= BEGIN

IMPORTS
    MODULE-IDENTITY, OBJECT-TYPE, NOTIFICATION-TYPE,
    Integer32, Unsigned32, IpAddress
        FROM    SNMPv2-SMI
    MacAddress, DisplayString, TruthValue
        FROM    SNMPv2-TC
    MODULE-COMPLIANCE, OBJECT-GROUP, NOTIFICATION-GROUP
        FROM    SNMPv2-CONF
    alvarionMgmtV2
        FROM    ALVARION-SMI
    AlvarionNotificationEnable, AlvarionSSIDOrNone
        FROM    ALVARION-TC
;


alvarionSatelliteManagementMIB  MODULE-IDENTITY
    LAST-UPDATED    "200710310000Z"
    ORGANIZATION    "Alvarion Ltd."
    CONTACT-INFO    "Alvarion Ltd.
                     Postal: 21a HaBarzel St.
                             P.O. Box 13139
                             Tel-Aviv 69710
                             Israel
                     Phone:  +972 3 645 6262"
    DESCRIPTION     "Alvarion SatelliteManagement MIB."

    ::= { alvarionMgmtV2 7 }


-- alvarionSatelliteManagementMIB definition
alvarionSatelliteManagementMIBObjects OBJECT IDENTIFIER ::= { alvarionSatelliteManagementMIB 1 }

-- MIB defines the following groupings
satelliteInfo   OBJECT IDENTIFIER ::= { alvarionSatelliteManagementMIBObjects 1 }
masterSettings  OBJECT IDENTIFIER ::= { alvarionSatelliteManagementMIBObjects 2 }

-- Satellite Information
satelliteTable OBJECT-TYPE
    SYNTAX      SEQUENCE OF SatelliteEntry
    MAX-ACCESS  not-accessible
    STATUS      current
    DESCRIPTION "The table of all satellite access points currently registered
                 by the Master access point. In tabular form to allow multiple
                 instance on an agent."
    ::= { satelliteInfo 1 }

satelliteEntry OBJECT-TYPE
    SYNTAX      SatelliteEntry
    MAX-ACCESS  not-accessible
    STATUS      current
    DESCRIPTION "Information about a Satellite access point currently registered
                 by the Master access point.
                 satelliteIndex - Uniquely identifies a device in the satellite
                                  table."
    INDEX       { satelliteIndex }
    ::= { satelliteTable 1 }

SatelliteEntry ::= SEQUENCE
{
    satelliteIndex                      Integer32,
    satelliteDeviceId                   DisplayString,
    satelliteMacAddress                 MacAddress,
    satelliteIpAddress                  IpAddress,
    satelliteName                       DisplayString,
    satelliteSSID                       AlvarionSSIDOrNone,
    satelliteChannelNumber              Unsigned32,
    satelliteForwardWirelessToWireless  TruthValue,
    satelliteMasterTrafficOnly          TruthValue,
    satelliteSNMPPort                   Integer32,
    satelliteSecureWebPort              Integer32,
    satelliteDeviceMacAddress           MacAddress,
    satelliteProductName                DisplayString,
    satelliteFirmwareRevision           DisplayString,
    satelliteGroupName                  DisplayString,
    satelliteChannelNumberRadio2        Unsigned32,
    satelliteVLAN                       Integer32,
    satelliteDetectionPort              DisplayString
}

satelliteIndex OBJECT-TYPE
    SYNTAX      Integer32 (1..2147483647)
    MAX-ACCESS  not-accessible
    STATUS      current
    DESCRIPTION "Index of a the satellite in the satelliteTable."
    ::= { satelliteEntry 1 }

satelliteDeviceId OBJECT-TYPE
    SYNTAX      DisplayString
    MAX-ACCESS  read-only
    STATUS      current
    DESCRIPTION "Device ID of a the satellite in the satelliteTable."
    ::= { satelliteEntry 2 }

satelliteMacAddress OBJECT-TYPE
    SYNTAX      MacAddress
    MAX-ACCESS  read-only
    STATUS      current
    DESCRIPTION "Indicates the MAC address of the wireless radio of the
                 satellite access point."
    ::= { satelliteEntry 3 }

satelliteIpAddress OBJECT-TYPE
    SYNTAX      IpAddress
    MAX-ACCESS  read-only
    STATUS      current
    DESCRIPTION "Indicates the IP address of the satellite access point."
    ::= { satelliteEntry 4 }

satelliteName OBJECT-TYPE
    SYNTAX      DisplayString
    MAX-ACCESS  read-only
    STATUS      current
    DESCRIPTION "Indicates the name of the satellite access point."
    ::= { satelliteEntry 5 }

satelliteSSID OBJECT-TYPE
    SYNTAX      AlvarionSSIDOrNone
    MAX-ACCESS  read-only
    STATUS      current
    DESCRIPTION "Indicates the SSID of the satellite access point."
    ::= { satelliteEntry 6 }

satelliteChannelNumber OBJECT-TYPE
    SYNTAX      Unsigned32
    MAX-ACCESS  read-only
    STATUS      current
    DESCRIPTION "Indicates the wireless channel number the satellite
                 access point is operating on."
    ::= { satelliteEntry 7 }

satelliteForwardWirelessToWireless OBJECT-TYPE
    SYNTAX      TruthValue
    MAX-ACCESS  read-only
    STATUS      current
    DESCRIPTION "Indicates if the forwarding of traffic between wireless client
                 stations is enabled on the satellite access point.
                   'true': indicates that the forwarding feature is enabled,
                   'false': indicates that no forwarding takes place."
    ::= { satelliteEntry 8 }

satelliteMasterTrafficOnly OBJECT-TYPE
    SYNTAX      TruthValue
    MAX-ACCESS  read-only
    STATUS      current
    DESCRIPTION "Indicates if the satellite will only forward traffic that
                 is addressed to the MAC address of the Master access point."
    ::= { satelliteEntry 9 }

satelliteSNMPPort OBJECT-TYPE
    SYNTAX      Integer32 (0..65535)
    MAX-ACCESS  read-only
    STATUS      current
    DESCRIPTION "Indicates the SNMP port on which the satellite listens.
                 The value zero is used when no information could be
                 retrieved from the satellite device."
    ::= { satelliteEntry 10 }

satelliteSecureWebPort  OBJECT-TYPE
    SYNTAX      Integer32 (0..65535)
    MAX-ACCESS  read-only
    STATUS      current
    DESCRIPTION "Indicates the secure web port on which the satellite listens.
                The value zero is used when no information could be
                retrieved from the satellite device."
    ::= { satelliteEntry 11 }

satelliteDeviceMacAddress OBJECT-TYPE
    SYNTAX      MacAddress
    MAX-ACCESS  read-only
    STATUS      current
    DESCRIPTION "Indicates the MAC address of the satellite access point
                 bridge interface."
    ::= { satelliteEntry 12 }

satelliteProductName OBJECT-TYPE
    SYNTAX      DisplayString
    MAX-ACCESS  read-only
    STATUS      current
    DESCRIPTION "Indicates the Alvarion product name for the device
                 in printable ASCII characters."
    ::= { satelliteEntry 13 }

satelliteFirmwareRevision OBJECT-TYPE
    SYNTAX      DisplayString
    MAX-ACCESS  read-only
    STATUS      current
    DESCRIPTION "Indicates the revision number of the device firmware in
                 printable ASCII characters."
    ::= { satelliteEntry 14 }

satelliteGroupName OBJECT-TYPE
    SYNTAX      DisplayString
    MAX-ACCESS  read-only
    STATUS      current
    DESCRIPTION "Indicates the location-aware group name of the satellite.
                 The group name is only returned when location-aware is
		     enabled at the satellite. An empty string is returned
		     otherwise."
    ::= { satelliteEntry 15 }

satelliteChannelNumberRadio2 OBJECT-TYPE
    SYNTAX      Unsigned32
    MAX-ACCESS  read-only
    STATUS      current
    DESCRIPTION "Indicates the wireless channel number the radio 2 is
                 operating on."
    ::= { satelliteEntry 16 }

satelliteVLAN OBJECT-TYPE
    SYNTAX      Integer32
    MAX-ACCESS  read-only
    STATUS      current
    DESCRIPTION "Management VLAN."
    ::= { satelliteEntry 17 }

satelliteDetectionPort OBJECT-TYPE
    SYNTAX      DisplayString
    MAX-ACCESS  read-only
    STATUS      current
    DESCRIPTION "The detection packet is send on this interface."
    ::= { satelliteEntry 18 }

satelliteNumber OBJECT-TYPE
    SYNTAX      Unsigned32
    MAX-ACCESS  read-only
    STATUS      current
    DESCRIPTION "Indicates the number of satellites present in the satellite table."
    ::= { satelliteInfo 2 }


-- satellite notification configuration
satelliteUpNotificationEnabled OBJECT-TYPE
    SYNTAX      AlvarionNotificationEnable
    MAX-ACCESS  read-write
    STATUS      current
    DESCRIPTION "Specifies if satelliteUpNotification notifications are generated."
    DEFVAL      { enable }
    ::= { masterSettings 1 }

satelliteDownNotificationEnabled OBJECT-TYPE
    SYNTAX      AlvarionNotificationEnable
    MAX-ACCESS  read-write
    STATUS      current
    DESCRIPTION "Specifies if satelliteDownNotification notifications are generated."
    DEFVAL      { enable }
    ::= { masterSettings 2 }

-- Satellite notifications
alvarionSatelliteManagementMIBNotificationPrefix OBJECT IDENTIFIER ::= { alvarionSatelliteManagementMIB 2 }
alvarionSatelliteManagementMIBNotifications OBJECT IDENTIFIER ::= { alvarionSatelliteManagementMIBNotificationPrefix 0 }

satelliteUpNotification NOTIFICATION-TYPE
    OBJECTS     {
                    satelliteName,
                    satelliteDeviceId,
                    satelliteMacAddress,
                    satelliteIpAddress,
                    satelliteSSID
                }
    STATUS      current
    DESCRIPTION "Sent when a new satellite is detected."
    ::= { alvarionSatelliteManagementMIBNotifications  1 }

satelliteDownNotification NOTIFICATION-TYPE
    OBJECTS     {
                    satelliteName,
                    satelliteDeviceId,
                    satelliteMacAddress,
                    satelliteIpAddress,
                    satelliteSSID
                }
    STATUS      current
    DESCRIPTION "Sent when a satellite becomes unreachable."
    ::= { alvarionSatelliteManagementMIBNotifications 2 }

-- conformance information
alvarionSatelliteManagementMIBConformance OBJECT IDENTIFIER ::= { alvarionSatelliteManagementMIB 3 }
alvarionSatelliteManagementMIBCompliances OBJECT IDENTIFIER ::= { alvarionSatelliteManagementMIBConformance 1 }
alvarionSatelliteManagementMIBGroups      OBJECT IDENTIFIER ::= { alvarionSatelliteManagementMIBConformance 2 }

-- compliance statements
alvarionSatelliteManagementMIBCompliance MODULE-COMPLIANCE
    STATUS      current
    DESCRIPTION "The compliance statement for entities which implement
                 the Alvarion SatelliteManagement MIB."
    MODULE      MANDATORY-GROUPS
                    {
                        alvarionSatelliteManagementMIBGroup,
                        alvarionSatelliteNotificationControlGroup,
                        alvarionSatelliteNotificationGroup

                    }
    ::= { alvarionSatelliteManagementMIBCompliances 1 }

-- units of conformance
alvarionSatelliteManagementMIBGroup OBJECT-GROUP
    OBJECTS     {
                    satelliteDeviceId,
                    satelliteMacAddress,
                    satelliteIpAddress,
                    satelliteName,
                    satelliteSSID,
                    satelliteChannelNumber,
                    satelliteForwardWirelessToWireless,
                    satelliteMasterTrafficOnly,
                    satelliteSNMPPort,
                    satelliteSecureWebPort,
                    satelliteDeviceMacAddress,
                    satelliteProductName,
                    satelliteFirmwareRevision,
                    satelliteGroupName,
                    satelliteNumber,
                    satelliteChannelNumberRadio2,
                    satelliteVLAN,
                    satelliteDetectionPort
                }
    STATUS      current
    DESCRIPTION "A collection of objects providing the Satellite Management MIB
                 capability."
    ::= { alvarionSatelliteManagementMIBGroups 1 }

alvarionSatelliteNotificationControlGroup OBJECT-GROUP
    OBJECTS     {
                    satelliteUpNotificationEnabled,
                    satelliteDownNotificationEnabled
                }
    STATUS      current
    DESCRIPTION "A collection of objects providing the Satellite Management MIB
                 notification control capability."
    ::= { alvarionSatelliteManagementMIBGroups 2 }

alvarionSatelliteNotificationGroup NOTIFICATION-GROUP
    NOTIFICATIONS   {
                        satelliteUpNotification,
                        satelliteDownNotification
                    }
    STATUS      current
    DESCRIPTION "A collection of supported notifications."
    ::= { alvarionSatelliteManagementMIBGroups 3 }

END
