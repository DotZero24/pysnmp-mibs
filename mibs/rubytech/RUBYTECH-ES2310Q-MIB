RUBYTECH-ES2310Q-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    ifIndex    FROM RFC1213-MIB;

-- @ENTERPRISE-SECTION-START
rubytech MODULE-IDENTITY
        LAST-UPDATED "200606160000Z"
        ORGANIZATION "Ruby Tech Corp."
        CONTACT-INFO
            "2F, No.7, Lane 50, Nan Kang Road, Sec.3, Taipei, Taiwan
             Email: rubytech@mail.rubytech.com.tw
             TEL: 886-2-2785-3961
             FAX: 886-2-2786-3012"
        DESCRIPTION
            "The MIB module for Ruby Tech."
        ::= { enterprises 5205 }

switch               OBJECT IDENTIFIER ::= { rubytech 2 }

es2310qProductID	        OBJECT IDENTIFIER ::= { switch 24 }
-- @ENTERPRISE-SECTION-END

es2310qProduces            OBJECT IDENTIFIER ::= { es2310qProductID 1 }

es2310qSystem           	OBJECT IDENTIFIER ::= { es2310qProduces 1 }

es2310qCommonSys           	OBJECT IDENTIFIER ::= { es2310qSystem 1 }

es2310qReboot OBJECT-TYPE
	SYNTAX		INTEGER(0|1|2)
	MAX-ACCESS	    read-write
	STATUS		current
	DESCRIPTION
		"reboot the system. Get this oid always return zero.
            0 - do nothing
			1 - reboot without saving start
			2 - reboot with saving start"
--	@@ACTION	ruby_common_sys
	::= { es2310qCommonSys 1 }

es2310qBiosVsersion	OBJECT-TYPE
	SYNTAX		DisplayString
	MAX-ACCESS	    read-only
	STATUS		current
	DESCRIPTION
		"Get the BIOS version of the system."
--	@@ACTION	ruby_common_sys
	::= { es2310qCommonSys 2 }

es2310qFirmwareVersion	OBJECT-TYPE
	SYNTAX		DisplayString
	MAX-ACCESS	    read-only
	STATUS		current
	DESCRIPTION
		"Get the firmware version of the system."
--	@@ACTION	ruby_common_sys
	::= { es2310qCommonSys 3 }

es2310qHardwareVersion	OBJECT-TYPE
	SYNTAX		DisplayString
	MAX-ACCESS	    read-only
	STATUS		current
	DESCRIPTION
		"Get the hardware version of the system."
--	@@ACTION	ruby_common_sys
	::= { es2310qCommonSys 4 }

es2310qMechanicalVersion OBJECT-TYPE
	SYNTAX		DisplayString
	MAX-ACCESS 	    read-only
	STATUS		current
	DESCRIPTION
		"Get the mechanical version of the system."
--	@@ACTION	ruby_common_sys
	::= { es2310qCommonSys 5 }

es2310qSerialNumber	OBJECT-TYPE
	SYNTAX		DisplayString
	MAX-ACCESS	    read-only
	STATUS		current
	DESCRIPTION
		"Get the serial number of the system."
--	@@ACTION	ruby_common_sys
	::= { es2310qCommonSys 6 }

es2310qHostMacAddress	OBJECT-TYPE
	SYNTAX		DisplayString
	MAX-ACCESS	    read-only
	STATUS		current
	DESCRIPTION
		"Get the MAC address of the system."
--	@@ACTION	ruby_common_sys
	::= { es2310qCommonSys 7 }

es2310qDevicePort	OBJECT-TYPE
	SYNTAX		DisplayString
	MAX-ACCESS  	read-only
	STATUS		current
	DESCRIPTION
		"Get the quantity of ports that this system owns now."
--	@@ACTION	ruby_common_sys
	::= { es2310qCommonSys 8 }

es2310qRamSize  OBJECT-TYPE
    SYNTAX      DisplayString
    MAX-ACCESS      read-only
    STATUS      current
    DESCRIPTION
        "Get the RAM size of the system."
--	@@ACTION	ruby_common_sys
	::= { es2310qCommonSys 9 }

es2310qFlashSize  OBJECT-TYPE
    SYNTAX      DisplayString
    MAX-ACCESS      read-only
    STATUS      current
    DESCRIPTION
        "Get the flash size of the system."
--	@@ACTION	ruby_common_sys
	::= { es2310qCommonSys 10 }

es2310qIP           	OBJECT IDENTIFIER ::= { es2310qSystem 2 }

es2310qDhcpSetting OBJECT-TYPE
	SYNTAX		    INTEGER(0|1)
	MAX-ACCESS	        read-write
	STATUS		    current
	DESCRIPTION
		"Get/Set DHCP status of the system.
			0 - DHCP disable
			1 - DHCP enable"
--	@@ACTION	ruby_sys_ip
	::= { es2310qIP 1 }

es2310qIPAddress OBJECT-TYPE
	SYNTAX      IpAddress
	MAX-ACCESS	    read-write
	STATUS		current
	DESCRIPTION
		"Get/Set the IP address of the system.
		 Can't Set this OID if DHCP status is enabled."
--	@@ACTION	ruby_sys_ip
	::= { es2310qIP 2 }

es2310qNetMask OBJECT-TYPE
	SYNTAX      IpAddress
	MAX-ACCESS	    read-write
	STATUS		current
	DESCRIPTION
		"Get/Set the netmask of the system.
		 Can't Set this OID if DHCP status is enabled."
--	@@ACTION	ruby_sys_ip
	::= { es2310qIP 3 }

es2310qDefaultGateway OBJECT-TYPE
	SYNTAX      IpAddress
	MAX-ACCESS	    read-write
	STATUS		current
	DESCRIPTION
		"Get/Set the default gateway of the system.
		 Can't Set this OID if DHCP status is enabled."
--	@@ACTION	ruby_sys_ip
	::= { es2310qIP 4 }

es2310qDnsSetting OBJECT-TYPE
	SYNTAX      INTEGER(0|1)
	MAX-ACCESS	    read-write
	STATUS		current
	DESCRIPTION
		"Get/Set the source of DNS server.
		 Can't Set this OID if DHCP status is disabled.
			0 - manual, the DNS server is from manaul setting
            1 - auto, the DNS server is assigned by DHCP server."
--	@@ACTION	ruby_sys_ip
	::= { es2310qIP 5 }

es2310qDnsServer OBJECT-TYPE
	SYNTAX      IpAddress
	MAX-ACCESS	    read-write
	STATUS		current
	DESCRIPTION
		"Get/Set the DNS server of the system."
--	@@ACTION	ruby_sys_ip
	::= { es2310qIP 6 }

es2310qTime           	OBJECT IDENTIFIER ::= { es2310qSystem 3 }

es2310qSystemCurrentTime OBJECT-TYPE
	SYNTAX      DisplayString
	MAX-ACCESS	    read-only
	STATUS		current
	DESCRIPTION
		"Get the current time in the system."
--	@@ACTION	ruby_sys_time
	::= { es2310qTime 1 }

es2310qManualTimeSetting OBJECT-TYPE
	SYNTAX      DisplayString
	MAX-ACCESS	    read-write
	STATUS		current
	DESCRIPTION
		"Get/Set the system time of the device.
        The input format is 'Year/Month/Day/Hour/Minute/Second'.
        ex: 2004/1/1/12/34/25  means 2004/1/1 - 12:24:25 .
        value range:
        Year    : 2000 - 2036,
        Mouth   : 1 - 12,
        Day     : 1 - 31,
        Hour    : 0 - 23,
        Minute  : 0 - 59,
        sec     : 0 - 59."
--	@@ACTION	ruby_sys_time
	::= { es2310qTime 2 }

es2310qNTPServer OBJECT-TYPE
	SYNTAX      DisplayString
	MAX-ACCESS	    read-write
	STATUS		current
	DESCRIPTION
		"Get/Set the NTP Time Server. You can use the IP address or domain name."
--	@@ACTION	ruby_sys_time
	::= { es2310qTime 3 }

es2310qNTPTimeZone OBJECT-TYPE
	SYNTAX      INTEGER(-12..13)
	MAX-ACCESS	    read-write
	STATUS		current
	DESCRIPTION
		"Get/Set the NTP Time Zone.
		value range is between -12 and 13
		-12 - GMT -12:00,
		-11 - GMT -11:00,
		-10 - GMT -10:00,
		 -9 - GMT -09:00,
		 -8 - GMT -08:00,
		 -7 - GMT -07:00,
		 -6 - GMT -06:00,
		 -5 - GMT -05:00,
		 -4 - GMT -04:00,
		 -3 - GMT -03:00,
		 -2 - GMT -02:00,
		 -1 - GMT -01:00,
		  0 - GMT +00:00,
		  1 - GMT +01:00,
		  2 - GMT +02:00,
		  3 - GMT +03:00,
		  4 - GMT +04:00,
		  5 - GMT +05:00,
		  6 - GMT +06:00,
		  7 - GMT +07:00,
		  8 - GMT +08:00,
		  9 - GMT +09:00,
		 10 - GMT +10:00,
		 11 - GMT +11:00,
		 12 - GMT +12:00,
		 13 - GMT +13:00. "
--	@@ACTION	ruby_sys_time
	::= { es2310qTime 4 }

es2310qNTPTimeSync OBJECT-TYPE
	SYNTAX      INTEGER(0|1)
	MAX-ACCESS	    read-write
	STATUS		current
	DESCRIPTION
		"Sync time from NTP Server. Get this oid always return zero.
		Setting the Time Server and TimeZone before doing time sync.
		Notice that time server must be correct!
		value range (1|0):
		1 - sync.
        0 - do nothing."
--	@@ACTION	ruby_sys_time
	::= { es2310qTime 5 }

es2310qDaylightSavingTime OBJECT-TYPE
	SYNTAX      INTEGER(-5..5)
	MAX-ACCESS	    read-write
	STATUS		current
	DESCRIPTION
		"Get/Set the daylight saveing time.
		value range is between -5 and 5. unit: hour. "
--	@@ACTION	ruby_sys_time
	::= { es2310qTime 6 }

es2310qDaylightStartTime OBJECT-TYPE
	SYNTAX      DisplayString
	MAX-ACCESS	    read-write
	STATUS		current
	DESCRIPTION
		"Get/Set the Start time of Daylight Saving.
		The input format is 'MM/DD/HH',
		and daylight saving start month can't equal end month.
		example: month/day/hour   10/01/00
		month: 01~12, day: 01~31, hour: 00~23 ."
--	@@ACTION	ruby_sys_time
	::= { es2310qTime 7 }

es2310qDaylightEndTime OBJECT-TYPE
	SYNTAX      DisplayString
	MAX-ACCESS	    read-write
	STATUS		current
	DESCRIPTION
		"Get/Set the End time of Daylight Saving.
		The input format is 'MM/DD/HH',
		and daylight saving start month can't equal end month.
		example: month/day/hour   04/01/00
		month: 01~12, day: 01~31, hour: 00~23 ."
--	@@ACTION	ruby_sys_time
	::= { es2310qTime 8 }

es2310qAccount           	OBJECT IDENTIFIER ::= { es2310qSystem 4 }

es2310qAccountNumber OBJECT-TYPE
	SYNTAX      INTEGER(1..5)
	MAX-ACCESS	    read-only
	STATUS		current
	DESCRIPTION
		"Get the current account number(s) of the system."
--	@@ACTION	ruby_sys_account
	::= { es2310qAccount 1 }

es2310qAccountTable	OBJECT-TYPE
	SYNTAX		SEQUENCE OF ES2310QAccountEntry
	MAX-ACCESS	not-accessible
	STATUS		current
	DESCRIPTION
		"A list of es2310qAccountEntry. The number of entries are given by
		the value of es2310qAccountNumber."
	::= { es2310qAccount 2 }

ES2310QAccountEntry ::=
SEQUENCE {
    es2310qAccountIndex		    INTEGER,
    es2310qAccountAuthorization	DisplayString,
    es2310qAccountName             DisplayString,
    es2310qAccountPassword         DisplayString
}

es2310qAccountEntry	OBJECT-TYPE
	SYNTAX		ES2310QAccountEntry
	MAX-ACCESS	    not-accessible
	STATUS		current
	DESCRIPTION
		"Entry(s) for account informaion."
	INDEX {es2310qAccountIndex}
	::= { es2310qAccountTable 1 }

es2310qAccountIndex	OBJECT-TYPE
	SYNTAX		INTEGER(1..5)
	MAX-ACCESS	    read-only
	STATUS		current
	DESCRIPTION
		"The index of the account entry."
--	@@ACTION	ruby_sys_accountentry
	::= { es2310qAccountEntry 1 }

es2310qAccountAuthorization	OBJECT-TYPE
	SYNTAX		DisplayString
	MAX-ACCESS	    read-only
	STATUS		current
	DESCRIPTION
		"The authorization of the account entry."
--	@@ACTION	ruby_sys_accountentry
	::= { es2310qAccountEntry 2 }

es2310qAccountName	OBJECT-TYPE
	SYNTAX		DisplayString
	MAX-ACCESS	    read-write
	STATUS		current
	DESCRIPTION
		"The username of the account entry."
--	@@ACTION	ruby_sys_accountentry
	::= { es2310qAccountEntry 3 }

es2310qAccountPassword	OBJECT-TYPE
	SYNTAX		DisplayString
	MAX-ACCESS	    read-write
	STATUS		current
	DESCRIPTION
		"The password of the account entry. The return value is always '********'."
--	@@ACTION	ruby_sys_accountentry
	::= { es2310qAccountEntry 4 }

es2310qAccountAddName OBJECT-TYPE
	SYNTAX      DisplayString
	MAX-ACCESS	    read-write
	STATUS		current
	DESCRIPTION
		"The account name for adding operation."
--	@@ACTION	ruby_sys_account
	::= { es2310qAccount 3 }

es2310qAccountAddPassword OBJECT-TYPE
	SYNTAX      DisplayString
	MAX-ACCESS	    read-write
	STATUS		current
	DESCRIPTION
		"The account password for adding operation. The return value is aloways '********'."
--	@@ACTION	ruby_sys_account
	::= { es2310qAccount 4 }

es2310qDoAccountAdd OBJECT-TYPE
	SYNTAX      INTEGER(0|1)
	MAX-ACCESS	    read-write
	STATUS		current
	DESCRIPTION
		"Add account name. OID es2310qAccountAddName and es2310qAccountAddPassword must be
        filled first. Get this oid always return zero.
            1 - add account.
            0 - do nothing."
--	@@ACTION	ruby_sys_account
	::= { es2310qAccount 5 }

es2310qAccountDel	OBJECT-TYPE
	SYNTAX		INTEGER(2..5)
	MAX-ACCESS	    read-write
	STATUS		current
	DESCRIPTION
		"Delete account. The value is valid es2310qAccountIndex(Can't delete administrator)."
--	@@ACTION	ruby_sys_account
	::= { es2310qAccount 6 }


es2310qSnmp           	OBJECT IDENTIFIER ::= { es2310qProduces 2 }

es2310qGetCommunity OBJECT-TYPE
	SYNTAX      DisplayString
	MAX-ACCESS	    read-write
	STATUS		current
	DESCRIPTION
		"Get/Set the get-community of the SNMP."
--	@@ACTION	ruby_snmp
	::= { es2310qSnmp 1 }

es2310qSetCommunity OBJECT-TYPE
	SYNTAX      DisplayString
	MAX-ACCESS	    read-write
	STATUS		current
	DESCRIPTION
		"Get/Set the set-community of the SNMP."
--	@@ACTION	ruby_snmp
	::= { es2310qSnmp 2 }

es2310qTrapHostNumber OBJECT-TYPE
	SYNTAX      INTEGER(1..6)
	MAX-ACCESS	    read-only
	STATUS		current
	DESCRIPTION
		"Get the number of trap hosts."
--	@@ACTION	ruby_snmp
	::= { es2310qSnmp 3 }

es2310qTrapHostTable	OBJECT-TYPE
	SYNTAX		SEQUENCE OF ES2310QTrapHostEntry
	MAX-ACCESS	not-accessible
	STATUS		current
	DESCRIPTION
		"A list of trap host entry. The number of entries are given by the value of es2310qTrapHostNumber."
    ::= { es2310qSnmp 4 }

ES2310QTrapHostEntry ::=
SEQUENCE {
    es2310qTrapHostIndex		    INTEGER,
    es2310qTrapHostIP          	IpAddress,
    es2310qTrapHostPort            INTEGER,
    es2310qTrapHostCommunity       DisplayString
}

es2310qTrapHostEntry	OBJECT-TYPE
	SYNTAX		ES2310QTrapHostEntry
	MAX-ACCESS	    not-accessible
	STATUS		current
	DESCRIPTION
		"Entry information for trap host."
	INDEX {es2310qTrapHostIndex}
	::= { es2310qTrapHostTable 1 }

es2310qTrapHostIndex	OBJECT-TYPE
	SYNTAX		INTEGER(1..6)
	MAX-ACCESS	    read-only
	STATUS		current
	DESCRIPTION
		"The index of the trap host entry."
--	@@ACTION	ruby_snmp_trapentry
	::= { es2310qTrapHostEntry 1 }

es2310qTrapHostIP	OBJECT-TYPE
	SYNTAX		IpAddress
	MAX-ACCESS	    read-write
	STATUS		current
	DESCRIPTION
		"The IP of the trap host."
--	@@ACTION	ruby_snmp_trapentry
	::= { es2310qTrapHostEntry 2 }


es2310qTrapHostPort	OBJECT-TYPE
	SYNTAX		INTEGER(1..65535)
	MAX-ACCESS	    read-write
	STATUS		current
	DESCRIPTION
		"The receiving-port number of the trap host."
--	@@ACTION	ruby_snmp_trapentry
	::= { es2310qTrapHostEntry 3 }


es2310qTrapHostCommunity	OBJECT-TYPE
	SYNTAX		DisplayString
	MAX-ACCESS	    read-write
	STATUS		current
	DESCRIPTION
		"The community name for the trap PDU."
--	@@ACTION	ruby_snmp_trapentry
	::= { es2310qTrapHostEntry 4 }


es2310qAlarm           	OBJECT IDENTIFIER ::= { es2310qProduces 3 }

es2310qEvent           	OBJECT IDENTIFIER ::= { es2310qAlarm 1 }

es2310qEventNumber OBJECT-TYPE
	SYNTAX      INTEGER(1..2147483647)
	MAX-ACCESS	    read-only
	STATUS		current
	DESCRIPTION
		"Get the total number of alarm events."
--	@@ACTION	ruby_alarm_event
	::= { es2310qEvent 1 }

es2310qEventTable	OBJECT-TYPE
	SYNTAX		SEQUENCE OF ES2310QEventEntry
	MAX-ACCESS	not-accessible
	STATUS		current
    DESCRIPTION
        "A list of alarm event entry. The number of entries are given by the value of es2310qEventNumber."
	::= { es2310qEvent 2 }

ES2310QEventEntry ::=
SEQUENCE {
    es2310qEventIndex		    INTEGER,
    es2310qEventName          	DisplayString,
    es2310qEventSendEmail      INTEGER,
    es2310qEventSendSMS        INTEGER,
    es2310qEventSendTrap       INTEGER
}

es2310qEventEntry	OBJECT-TYPE
	SYNTAX		ES2310QEventEntry
	MAX-ACCESS	    not-accessible
	STATUS		current
	DESCRIPTION
		"Entry infomation for alarm event."
	INDEX {es2310qEventIndex}
	::= { es2310qEventTable 1 }

es2310qEventIndex	OBJECT-TYPE
	SYNTAX		INTEGER(1..2147483647)
	MAX-ACCESS	    read-only
	STATUS		current
	DESCRIPTION
		"The index of the alarm event entry."
--	@@ACTION	ruby_alarm_evententry
	::= { es2310qEventEntry 1 }

es2310qEventName	OBJECT-TYPE
	SYNTAX		DisplayString
	MAX-ACCESS	    read-only
	STATUS		current
	DESCRIPTION
		"The alarm event name."
--	@@ACTION	ruby_alarm_evententry
	::= { es2310qEventEntry 2 }

es2310qEventSendEmail	OBJECT-TYPE
	SYNTAX		INTEGER(0|1)
	MAX-ACCESS	    read-write
	STATUS		current
	DESCRIPTION
		"Send email when alarm event is triggered."
--	@@ACTION	ruby_alarm_evententry
	::= { es2310qEventEntry 3 }

es2310qEventSendSMS	OBJECT-TYPE
	SYNTAX		INTEGER(0|1)
	MAX-ACCESS	    read-write
	STATUS		current
	DESCRIPTION
		"Send sms when alarm event is triggered."
--	@@ACTION	ruby_alarm_evententry
	::= { es2310qEventEntry 4 }

es2310qEventSendTrap	OBJECT-TYPE
	SYNTAX		INTEGER(0|1)
	MAX-ACCESS	    read-write
	STATUS		current
	DESCRIPTION
		"Send trap when alarm event is triggered."
--	@@ACTION	ruby_alarm_evententry
	::= { es2310qEventEntry 5 }


es2310qEmail           	OBJECT IDENTIFIER ::= { es2310qAlarm 2 }

es2310qEmailServer OBJECT-TYPE
	SYNTAX      DisplayString
	MAX-ACCESS	    read-write
	STATUS		current
	DESCRIPTION
		"SMTP server for alarm event."
--	@@ACTION	ruby_alarm_email
	::= { es2310qEmail 1 }

es2310qEmailUsername OBJECT-TYPE
	SYNTAX      DisplayString
	MAX-ACCESS	    read-write
	STATUS		current
	DESCRIPTION
		"Username of smtp server."
--	@@ACTION	ruby_alarm_email
	::= { es2310qEmail 2 }

es2310qEmailPassword OBJECT-TYPE
	SYNTAX      DisplayString
	MAX-ACCESS	    read-write
	STATUS		current
	DESCRIPTION
		"User password of smtp server."
--	@@ACTION	ruby_alarm_email
	::= { es2310qEmail 3 }

es2310qEmailUserNumber OBJECT-TYPE
	SYNTAX      INTEGER(1..6)
	MAX-ACCESS	    read-only
	STATUS		current
	DESCRIPTION
		"The number of the email users that you want to send the alarm notification."
--	@@ACTION	ruby_alarm_email
	::= { es2310qEmail 4 }

es2310qEmailUserTable	OBJECT-TYPE
	SYNTAX		SEQUENCE OF ES2310QEmailUserEntry
	MAX-ACCESS	not-accessible
	STATUS		current
    DESCRIPTION
        "A list of email user entry. The number of entries are given by the value of es2310qEmailUserNumber."
	::= { es2310qEmail 5 }

ES2310QEmailUserEntry ::=
SEQUENCE {
    es2310qEmailUserIndex		    INTEGER,
    es2310qEmailUserAddress       	DisplayString
}

es2310qEmailUserEntry	OBJECT-TYPE
	SYNTAX		ES2310QEmailUserEntry
	MAX-ACCESS	    not-accessible
	STATUS		current
	DESCRIPTION
		"Entry information for email user entry."
	INDEX {es2310qEmailUserIndex}
	::= { es2310qEmailUserTable 1 }

es2310qEmailUserIndex	OBJECT-TYPE
	SYNTAX		INTEGER(1..6)
	MAX-ACCESS	    read-only
	STATUS		current
	DESCRIPTION
		"The index of the email user entry."
--	@@ACTION	ruby_alarm_emailentry
	::= { es2310qEmailUserEntry 1 }

es2310qEmailUserAddress	OBJECT-TYPE
	SYNTAX		DisplayString
	MAX-ACCESS	    read-write
	STATUS		current
	DESCRIPTION
		"The email address of the email user entry."
--	@@ACTION	ruby_alarm_emailentry
	::= { es2310qEmailUserEntry 2 }



es2310qSMS           	OBJECT IDENTIFIER ::= { es2310qAlarm 3 }

es2310qSMSServer OBJECT-TYPE
	SYNTAX      DisplayString
	MAX-ACCESS	    read-write
	STATUS		current
	DESCRIPTION
		"SMS server for alarm event."
--	@@ACTION	ruby_alarm_SMS
	::= { es2310qSMS 1 }

es2310qSMSUsername OBJECT-TYPE
	SYNTAX      DisplayString
	MAX-ACCESS	    read-write
	STATUS		current
	DESCRIPTION
		"Username of SMS server."
--	@@ACTION	ruby_alarm_SMS
	::= { es2310qSMS 2 }

es2310qSMSPassword OBJECT-TYPE
	SYNTAX      DisplayString
	MAX-ACCESS	    read-write
	STATUS		current
	DESCRIPTION
		"User password of SMS server."
--	@@ACTION	ruby_alarm_SMS
	::= { es2310qSMS 3 }

es2310qSMSUserNumber OBJECT-TYPE
	SYNTAX      INTEGER(1..6)
	MAX-ACCESS	    read-only
	STATUS		current
	DESCRIPTION
		"The number of the SMS users that you want to send the alarm notification."
--	@@ACTION	ruby_alarm_SMS
	::= { es2310qSMS 4 }

es2310qSMSUserTable	OBJECT-TYPE
	SYNTAX		SEQUENCE OF ES2310QSMSUserEntry
	MAX-ACCESS	not-accessible
	STATUS		current
    DESCRIPTION
        "A list of SMS user entry. The number of entries are given by the value of es2310qSMSUserNumber."
    ::= { es2310qSMS 5 }

ES2310QSMSUserEntry ::=
SEQUENCE {
    es2310qSMSUserIndex		    INTEGER,
    es2310qSMSUserMobilePhone       	DisplayString
}

es2310qSMSUserEntry	OBJECT-TYPE
	SYNTAX		ES2310QSMSUserEntry
	MAX-ACCESS	    not-accessible
	STATUS		current
	DESCRIPTION
		"Entry information for SMS user entry."
	INDEX {es2310qSMSUserIndex}
	::= { es2310qSMSUserTable 1 }

es2310qSMSUserIndex	OBJECT-TYPE
	SYNTAX		INTEGER(1..6)
	MAX-ACCESS	    read-only
	STATUS		current
	DESCRIPTION
		"The index of the SMS user entry."
--	@@ACTION	ruby_alarm_SMSentry
	::= { es2310qSMSUserEntry 1 }

es2310qSMSUserMobilePhone	OBJECT-TYPE
	SYNTAX		DisplayString
	MAX-ACCESS	    read-write
	STATUS		current
	DESCRIPTION
		"The SMS phone number of the SMS user entry."
--	@@ACTION	ruby_alarm_SMSentry
	::= { es2310qSMSUserEntry 2 }



es2310qTftp           	OBJECT IDENTIFIER ::= { es2310qProduces 4 }

es2310qTftpServer OBJECT-TYPE
	SYNTAX      IpAddress
	MAX-ACCESS	    read-write
	STATUS		current
	DESCRIPTION
		"Get/Set the tftp server."
--	@@ACTION	ruby_tftp
	::= { es2310qTftp 1 }


es2310qConfiguration           	OBJECT IDENTIFIER ::= { es2310qProduces 5 }

es2310qSaveRestore           	OBJECT IDENTIFIER ::= { es2310qConfiguration 1 }

es2310qSaveStart OBJECT-TYPE
	SYNTAX      INTEGER(0|1)
	MAX-ACCESS	    read-write
	STATUS		current
	DESCRIPTION
		"Save current configuration into flash memory (start section).
        Get this oid always return zero.
            1 - save.
            0 - do nothing. "
--	@@ACTION	ruby_config_save
	::= { es2310qSaveRestore 1 }

es2310qSaveUser OBJECT-TYPE
	SYNTAX      INTEGER(0|1)
	MAX-ACCESS	    read-write
	STATUS		current
	DESCRIPTION
		"Save current configuration into flash memory (user config section).
        Get this oid always return zero.
            1 - save.
            0 - do nothing. "
--	@@ACTION	ruby_config_save
	::= { es2310qSaveRestore 2 }

es2310qRestoreDefault OBJECT-TYPE
	SYNTAX      INTEGER(0|1|2)
	MAX-ACCESS	    read-write
	STATUS		current
	DESCRIPTION
		"Restore factory default configuration.
        Get this oid always return zero.
            2 - restore default included default ip address.
	    1 - restore default without changing current ip address.
            0 - do nothing. "
--	@@ACTION	ruby_config_save
	::= { es2310qSaveRestore 3 }

es2310qRestoreUser OBJECT-TYPE
	SYNTAX      INTEGER(0|1)
	MAX-ACCESS	    read-write
	STATUS		current
	DESCRIPTION
		"Restore user configurtion.
        Get this oid always return zero.
            1 - retore.
            0 - do nothing. "
--	@@ACTION	ruby_config_save
	::= { es2310qSaveRestore 4 }


es2310qConfigFile           	OBJECT IDENTIFIER ::= { es2310qConfiguration 2 }

es2310qExportConfigName OBJECT-TYPE
	SYNTAX      DisplayString
	MAX-ACCESS	    read-write
	STATUS		current
	DESCRIPTION
		"Get/Set export config file path and name."
--	@@ACTION	ruby_config_file
	::= { es2310qConfigFile 1 }

es2310qDoExportConfig OBJECT-TYPE
	SYNTAX      INTEGER(1|2)
	MAX-ACCESS	    read-write
	STATUS		current
	DESCRIPTION
		"Do export-config.
        Get this oid always return zero.
			1	-	export start section.
			2	-	export user-conf section."
--	@@ACTION	ruby_config_file
	::= { es2310qConfigFile 2 }

es2310qImportConfigName OBJECT-TYPE
	SYNTAX      DisplayString
	MAX-ACCESS	    read-write
	STATUS		current
	DESCRIPTION
        "Get/Set export config file path and name."
--	@@ACTION	ruby_config_file
	::= { es2310qConfigFile 3 }

es2310qDoImportConfig OBJECT-TYPE
	SYNTAX      INTEGER(1|2)
	MAX-ACCESS	    read-write
	STATUS		current
	DESCRIPTION
		"Do import-config.
        Get this oid always return zero.
			1	-	import start section.
			2	-	import user-conf section."
--	@@ACTION	ruby_config_file
	::= { es2310qConfigFile 4 }



es2310qDiagnostic           	OBJECT IDENTIFIER ::= { es2310qProduces 6 }

es2310qEEPROMTest OBJECT-TYPE
	SYNTAX      DisplayString
	MAX-ACCESS	    read-only
	STATUS		current
	DESCRIPTION
		"EEPROM access test."
--	@@ACTION	ruby_diagnostic
	::= { es2310qDiagnostic 1 }

es2310qUartTest OBJECT-TYPE
	SYNTAX      DisplayString
	MAX-ACCESS	    read-only
	STATUS		current
	DESCRIPTION
		"UART access test."
--	@@ACTION	ruby_diagnostic
	::= { es2310qDiagnostic 2 }

es2310qDramTest OBJECT-TYPE
	SYNTAX      DisplayString
	MAX-ACCESS	    read-only
	STATUS		current
	DESCRIPTION
		"DRAM access test."
--	@@ACTION	ruby_diagnostic
	::= { es2310qDiagnostic 3 }

es2310qFlashTest OBJECT-TYPE
	SYNTAX      DisplayString
	MAX-ACCESS	    read-only
	STATUS		current
	DESCRIPTION
		"Flash memory access test."
--	@@ACTION	ruby_diagnostic
	::= { es2310qDiagnostic 4 }

es2310qInternalLoopbackTest OBJECT-TYPE
	SYNTAX      DisplayString
	MAX-ACCESS	    read-only
	STATUS		current
	DESCRIPTION
		"Internel loopback test."
--	@@ACTION	ruby_diagnostic
	::= { es2310qDiagnostic 5 }

es2310qExternalLoopbackTest OBJECT-TYPE
	SYNTAX      DisplayString
	MAX-ACCESS	    read-only
	STATUS		current
	DESCRIPTION
		"Externel loopback test."
--	@@ACTION	ruby_diagnostic
	::= { es2310qDiagnostic 6 }

es2310qPingTest OBJECT-TYPE
	SYNTAX      DisplayString
	MAX-ACCESS	    read-write
	STATUS		current
	DESCRIPTION
		"Set the host address that you want to ping and the system will return the test result."
--	@@ACTION	ruby_diagnostic
	::= { es2310qDiagnostic 7 }



es2310qLog           	OBJECT IDENTIFIER ::= { es2310qProduces 7 }

es2310qClearLog OBJECT-TYPE
	SYNTAX      INTEGER(0|1)
	MAX-ACCESS	    read-write
	STATUS		current
	DESCRIPTION
		"Clear system log.
        Get this oid always return zero.
            1 - clear log.
            0 - do nothing. "
--	@@ACTION	ruby_log
	::= { es2310qLog 1 }

es2310qUploadLog OBJECT-TYPE
	SYNTAX      INTEGER(0|1)
	MAX-ACCESS	    read-write
	STATUS		current
	DESCRIPTION
		"Upload current system log. Set the correct tftp server first.
        The format of log file is 'ModelName_SerialNumbuer_YYMMDD_HHMM'.
        Get this oid always return zero.
            1 - upload log
            0 - do nothing. "
--	@@ACTION	ruby_log
	::= { es2310qLog 2 }

es2310qAutoUploadLogState OBJECT-TYPE
	SYNTAX      INTEGER(0|1)
	MAX-ACCESS	    read-write
	STATUS		current
	DESCRIPTION
		"Enable log auto-upload function. Set the correct tftp server first.
        The format of log file is 'ModelName_SerialNumbuer_YYMMDD_HHMM'.
        Get this oid always return zero.
            1 - Enable auto-upload
            0 - do nothing. "
--	@@ACTION	ruby_log
	::= { es2310qLog 3 }

es2310qLogNumber OBJECT-TYPE
	SYNTAX      INTEGER(0..120)
	MAX-ACCESS	    read-only
	STATUS		current
	DESCRIPTION
		"Get the number of current system log. "
--	@@ACTION	ruby_log
	::= { es2310qLog 4 }

es2310qLogTable	OBJECT-TYPE
	SYNTAX		SEQUENCE OF ES2310QLogEntry
	MAX-ACCESS	not-accessible
	STATUS		current
    DESCRIPTION
        "A list of log entry. The number of entries are given by the value of es2310qLogNumber."
	::= { es2310qLog 5 }

ES2310QLogEntry ::=
SEQUENCE {
    es2310qLogIndex		    INTEGER,
    es2310qLogEvent           	DisplayString
}

es2310qLogEntry	OBJECT-TYPE
	SYNTAX		ES2310QLogEntry
	MAX-ACCESS	    not-accessible
	STATUS		current
	DESCRIPTION
		"Entry information for system log."
	INDEX {es2310qLogIndex}
	::= { es2310qLogTable 1 }

es2310qLogIndex	OBJECT-TYPE
	SYNTAX		INTEGER(1..120)
	MAX-ACCESS	    read-only
	STATUS		current
	DESCRIPTION
		"The index of the log entry."
--	@@ACTION	ruby_logentry
	::= { es2310qLogEntry 1 }

es2310qLogEvent	OBJECT-TYPE
	SYNTAX		DisplayString
	MAX-ACCESS	    read-only
	STATUS		current
	DESCRIPTION
		"The detail information of the log entry."
--	@@ACTION	ruby_logentry
	::= { es2310qLogEntry 2 }



es2310qFirmware           	OBJECT IDENTIFIER ::= { es2310qProduces 8 }

es2310qFirmwareFileName OBJECT-TYPE
	SYNTAX      DisplayString
	MAX-ACCESS	    read-write
	STATUS		current
	DESCRIPTION
		"Get/Set the path and filename for firmware upgrading."
--	@@ACTION	ruby_Firmware
	::= { es2310qFirmware 1 }

es2310qDoFirmwareUpgrade OBJECT-TYPE
	SYNTAX      INTEGER(0|1)
	MAX-ACCESS	    read-write
	STATUS		current
	DESCRIPTION
		"Do firmware upgrade. Get this oid always return zero.
            1 - do firmware upgrade.
            0 - do nothing."
--	@@ACTION	ruby_Firmware
	::= { es2310qFirmware 2 }



es2310qPort           	OBJECT IDENTIFIER ::= { es2310qProduces 9 }

es2310qPortStatus           	OBJECT IDENTIFIER ::= { es2310qPort 1 }

es2310qPortStatusNumber OBJECT-TYPE
	SYNTAX      INTEGER(1..2147483647)
	MAX-ACCESS	    read-only
	STATUS		current
	DESCRIPTION
		"Get the number of port state."
--	@@ACTION	ruby_port_status
	::= { es2310qPortStatus 1 }

es2310qPortStatusTable	OBJECT-TYPE
	SYNTAX		SEQUENCE OF ES2310QPortStatusEntry
	MAX-ACCESS	not-accessible
	STATUS		current
    DESCRIPTION
        "A list of port status entry. The number of entries are given by the value of es2310qPortStatusNumber."
	::= { es2310qPortStatus 2 }

ES2310QPortStatusEntry ::=
SEQUENCE {
    es2310qPortStatusIndex		    INTEGER,
    es2310qPortStatusMedia          DisplayString,
    es2310qPortStatusLink           DisplayString,
    es2310qPortStatusPortState      DisplayString,
    es2310qPortStatusAutoNego       DisplayString,
    es2310qPortStatusSpdDpx         DisplayString,
    es2310qPortStatusRxPause        DisplayString,
    es2310qPortStatusTxPause        DisplayString,
    es2310qPortStatusDescription     DisplayString
}

es2310qPortStatusEntry	OBJECT-TYPE
	SYNTAX		ES2310QPortStatusEntry
	MAX-ACCESS	    not-accessible
	STATUS		current
	DESCRIPTION
		"Entry(s) for port status informaion."
	INDEX {es2310qPortStatusIndex}
	::= { es2310qPortStatusTable 1 }

es2310qPortStatusIndex	OBJECT-TYPE
	SYNTAX		INTEGER(1..2147483647)
	MAX-ACCESS	    read-only
	STATUS		current
	DESCRIPTION
		"The index of the port status entry."
--	@@ACTION	ruby_port_status_entry
	::= { es2310qPortStatusEntry 1 }

es2310qPortStatusMedia	OBJECT-TYPE
	SYNTAX		DisplayString
	MAX-ACCESS	    read-only
	STATUS		current
	DESCRIPTION
		"The port media type of the port status entry."
--	@@ACTION	ruby_port_status_entry
	::= { es2310qPortStatusEntry 2 }

es2310qPortStatusLink	OBJECT-TYPE
	SYNTAX		DisplayString
	MAX-ACCESS	    read-only
	STATUS		current
	DESCRIPTION
		"The port link of the port status entry."
--	@@ACTION	ruby_port_status_entry
	::= { es2310qPortStatusEntry 3 }

es2310qPortStatusPortState	OBJECT-TYPE
	SYNTAX		DisplayString
	MAX-ACCESS	    read-only
	STATUS		current
	DESCRIPTION
		"The port state of the port status entry."
--	@@ACTION	ruby_port_status_entry
	::= { es2310qPortStatusEntry 4 }

es2310qPortStatusAutoNego	OBJECT-TYPE
	SYNTAX		DisplayString
	MAX-ACCESS	    read-only
	STATUS		current
	DESCRIPTION
		"The auto negotiation of the port status entry."
--	@@ACTION	ruby_port_status_entry
	::= { es2310qPortStatusEntry 5 }

es2310qPortStatusSpdDpx 	OBJECT-TYPE
	SYNTAX		DisplayString
	MAX-ACCESS	    read-only
	STATUS		current
	DESCRIPTION
		"The speed/duplex of the port status entry."
--	@@ACTION	ruby_port_status_entry
	::= { es2310qPortStatusEntry 6 }

es2310qPortStatusRxPause 	OBJECT-TYPE
	SYNTAX		DisplayString
	MAX-ACCESS	    read-only
	STATUS		current
	DESCRIPTION
		"The Rx Pause of the port status entry."
--	@@ACTION	ruby_port_status_entry
	::= { es2310qPortStatusEntry 7 }

es2310qPortStatusTxPause 	OBJECT-TYPE
	SYNTAX		DisplayString
	MAX-ACCESS	    read-only
	STATUS		current
	DESCRIPTION
		"The Tx Pause of the port status entry."
--	@@ACTION	ruby_port_status_entry
	::= { es2310qPortStatusEntry 8 }

es2310qPortStatusDescription	OBJECT-TYPE
	SYNTAX		DisplayString
	MAX-ACCESS	read-only
	STATUS		current
	DESCRIPTION
		"The description of port."
--	@@ACTION	ruby_port_status_entry
	::= { es2310qPortStatusEntry 9 }

es2310qPortConf           	OBJECT IDENTIFIER ::= { es2310qPort 2 }

es2310qPortConfNumber OBJECT-TYPE
	SYNTAX      INTEGER(1..2147483647)
	MAX-ACCESS	    read-only
	STATUS		current
	DESCRIPTION
		"Get the number of port configuration."
--	@@ACTION	ruby_port_conf
	::= { es2310qPortConf 1 }

es2310qPortConfTable	OBJECT-TYPE
	SYNTAX		SEQUENCE OF ES2310QPortConfEntry
	MAX-ACCESS	not-accessible
	STATUS		current
    DESCRIPTION
        "A list of port configuration entry. The number of entries are given by the value of es2310qPortConfNumber."
	::= { es2310qPortConf 2 }

ES2310QPortConfEntry ::=
SEQUENCE {
    es2310qPortConfIndex		    INTEGER,
    es2310qPortConfPortState        INTEGER,
    es2310qPortConfSpdDpx           INTEGER,
    es2310qPortConfFlwCtrl          INTEGER,
    es2310qPortConfDescription          DisplayString
}

es2310qPortConfEntry	OBJECT-TYPE
	SYNTAX		ES2310QPortConfEntry
	MAX-ACCESS	    not-accessible
	STATUS		current
	DESCRIPTION
		"Entry(s) for port configuration informaion."
	INDEX {es2310qPortConfIndex}
	::= { es2310qPortConfTable 1 }

es2310qPortConfIndex	OBJECT-TYPE
	SYNTAX		INTEGER(1..2147483647)
	MAX-ACCESS	    read-only
	STATUS		current
	DESCRIPTION
		"The index of the port configuration entry."
--	@@ACTION	ruby_port_conf_entry
	::= { es2310qPortConfEntry 1 }

es2310qPortConfPortState	OBJECT-TYPE
	SYNTAX		INTEGER(0|1)
	MAX-ACCESS	    read-write
	STATUS		current
	DESCRIPTION
		"The port state of the port configuration entry.
		 0 - disabled.
		 1 - enabled. "
--	@@ACTION	ruby_port_conf_entry
	::= { es2310qPortConfEntry 2 }

es2310qPortConfSpdDpx	OBJECT-TYPE
	SYNTAX		INTEGER(0..5)
	MAX-ACCESS	    read-write
	STATUS		current
	DESCRIPTION
		"The speed/duplex of the port configuration entry.
		 0 - auto.
		 1 - 10M/Half.
		 2 - 10M/Full.
		 3 - 100M/Half.
		 4 - 100M/Full."
--	@@ACTION	ruby_port_conf_entry
	::= { es2310qPortConfEntry 3 }

es2310qPortConfFlwCtrl	OBJECT-TYPE
	SYNTAX		INTEGER(0|1)
	MAX-ACCESS	    read-write
	STATUS		current
	DESCRIPTION
		"The flow control of the port configuration entry.
		 0 - asymmetric.
		 1 - symmetric.  "
--	@@ACTION	ruby_port_conf_entry
	::= { es2310qPortConfEntry 4 }

es2310qPortConfDescription	OBJECT-TYPE
	SYNTAX		DisplayString
	MAX-ACCESS	read-write
	STATUS		current
	DESCRIPTION
		"The description of port."
--	@@ACTION	ruby_port_conf_entry
	::= { es2310qPortConfEntry 5 }

es2310qLoopDetected           	OBJECT IDENTIFIER ::= { es2310qProduces 10 }

es2310qLoopDetectedNumber OBJECT-TYPE
	SYNTAX      INTEGER(1..2147483647)
	MAX-ACCESS	    read-only
	STATUS		current
	DESCRIPTION
		"Get the number of loop detected entry."
--	@@ACTION	ruby_loop_detect
	::= { es2310qLoopDetected 1 }

es2310qLoopDetectedTable	OBJECT-TYPE
	SYNTAX		SEQUENCE OF ES2310QLoopDetectedEntry
	MAX-ACCESS	not-accessible
	STATUS		current
    DESCRIPTION
        "A list of loop detected entry. The number of entries are given by the value of es2310qLoopDetectedNumber."
	::= { es2310qLoopDetected 2 }

ES2310QLoopDetectedEntry ::=
SEQUENCE {
    es2310qLoopDetectedfIndex           INTEGER,
    es2310qLoopDetectedStateEbl         INTEGER,
    es2310qLoopDetectedCurrentStatus    DisplayString,
    es2310qLoopDetectedRemoved          INTEGER
}

es2310qLoopDetectedEntry	OBJECT-TYPE
	SYNTAX		ES2310QLoopDetectedEntry
	MAX-ACCESS	    not-accessible
	STATUS		current
	DESCRIPTION
		"Entry(s) for loop detected informaion."
	INDEX {es2310qLoopDetectedfIndex}
	::= { es2310qLoopDetectedTable 1 }

es2310qLoopDetectedfIndex	OBJECT-TYPE
	SYNTAX		INTEGER(1..2147483647)
	MAX-ACCESS	    read-only
	STATUS		current
	DESCRIPTION
		"The index of the loop detected entry."
--	@@ACTION	ruby_loop_detect_entry
	::= { es2310qLoopDetectedEntry 1 }

es2310qLoopDetectedStateEbl	OBJECT-TYPE
	SYNTAX		INTEGER(0|1)
	MAX-ACCESS	    read-write
	STATUS		current
	DESCRIPTION
		"The state of the loop detected entry.
		 0 - disabled.
		 1 - enabled. "
--	@@ACTION	ruby_loop_detect_entry
	::= { es2310qLoopDetectedEntry 2 }

es2310qLoopDetectedCurrentStatus	OBJECT-TYPE
	SYNTAX		INTEGER(0|1)
	MAX-ACCESS	    read-only
	STATUS		current
	DESCRIPTION
		"The current status of the loop detected port.
         0 - unlocked
         1 - locked due to the loop condition "
--	@@ACTION	ruby_loop_detect_entry
	::= { es2310qLoopDetectedEntry 3 }

es2310qLoopDetectedRemoved	OBJECT-TYPE
	SYNTAX		INTEGER(0|1)
	MAX-ACCESS	    read-write
	STATUS		current
	DESCRIPTION
		"unlock the port which is locked due to loop condition. Get this oid always return zero.
         1 - unlock the port,
         0 - do nothing"
--	@@ACTION	ruby_loop_detect_entry
	::= { es2310qLoopDetectedEntry 4 }

es2310qLoopDetectedAction OBJECT-TYPE
	SYNTAX      INTEGER(0|1)
	MAX-ACCESS	    read-write
	STATUS		current
	DESCRIPTION
		"Set the corresponding action while loop is detected.
         1 - locket the loop port,
         0 - do nothing."
--	@@ACTION	ruby_loop_detect
	::= { es2310qLoopDetected 3 }

es2310qTrapEntry	       OBJECT IDENTIFIER ::= { es2310qProduces 20 }

es2310qModuleInserted NOTIFICATION-TYPE
    OBJECTS { ifIndex }
	STATUS    current
	DESCRIPTION
	    "Send this trap when a moudle is inserted to the system. The OID value means
	     the port number."
	::= { es2310qTrapEntry 1 }

es2310qModuleRemoved NOTIFICATION-TYPE
    OBJECTS { ifIndex }
	STATUS    current
	DESCRIPTION
	    "Send this trap when a moudule is removed from the system. The OID value means
	     the port number."
	::= { es2310qTrapEntry 2 }

es2310qDualMediaSwapped NOTIFICATION-TYPE
    OBJECTS { ifIndex }
	STATUS    current
	DESCRIPTION
	    "Send this trap when the dual media port changed. The OID value means the port number."
	::= { es2310qTrapEntry 3 }

es2310qPoEFailure NOTIFICATION-TYPE
	STATUS    current
	DESCRIPTION
	    "Send this trap while detecting the malfunction of PoE chips."
	::= { es2310qTrapEntry 4 }

es2310qLoopDetected NOTIFICATION-TYPE
    OBJECTS { ifIndex }
	STATUS    current
	DESCRIPTION
	    "Send this trap when loop condition has been detected. The OID value means the port number."
	::= { es2310qTrapEntry 5 }

es2310qStpStateDisabled NOTIFICATION-TYPE
	STATUS		current
	DESCRIPTION
	   "Send this trap when the operational state of STP is from enabled to disabled. "
	::= { es2310qTrapEntry 100 }

es2310qStpStateEnabled NOTIFICATION-TYPE
	STATUS		current
	DESCRIPTION
	   "Send this trap when the operational state of STP is from disabled to enabled. "
	::= { es2310qTrapEntry 101 }

es2310qStpTopologyChanged NOTIFICATION-TYPE
    OBJECTS { ifIndex }
	STATUS		current
	DESCRIPTION
	   "Send this trap when RSTP determines a port should enter the FORWARDING state
	    (a topology change occurs). The OID value is the ifIndex of the port that
	    produces the topology change"
	::= { es2310qTrapEntry 102 }

es2310qRmonRisingAlarm NOTIFICATION-TYPE
	STATUS		current
	DESCRIPTION
	   "Send this trap when an RMON rising alarm happened. The OID value is the value
	    of another OID variable sampled by the RMON Alarm Group that exceeds its
	    own RisingThreshold "
	::= { es2310qTrapEntry 110 }

es2310qRmonFallingAlarm NOTIFICATION-TYPE
	STATUS		current
	DESCRIPTION
           "Send this trap when an RMON falling alarm happened. The OID value is the value
	    of another OID variable sampled by the RMON Alarm Group that is smaller than its
	    own FallingThreshold "
	::= { es2310qTrapEntry 111 }

es2310qLacpStateDisabled NOTIFICATION-TYPE
    OBJECTS {ifIndex, groupId}
	STATUS		current
	DESCRIPTION
	   "Send this trap when the operational state of LACP is from enabled to disabled.
	    The OID value means the disabled Group ID."
	::= { es2310qTrapEntry 120 }

es2310qLacpStateEnabled NOTIFICATION-TYPE
    OBJECTS {ifIndex, groupId}
	STATUS		current
	DESCRIPTION
	   "Send this trap when the operational state of LACP is from disabled to enabled.
	    The OID value means the disabled Group ID."
	::= { es2310qTrapEntry 121 }

es2310qLacpPortAdded NOTIFICATION-TYPE
    OBJECTS   { ifIndex, actorkey, partnerkey }
	STATUS		current
	DESCRIPTION
	   "Send this trap when the state of port is in 'trunk ready'."
	::= { es2310qTrapEntry 123 }

es2310qLacpPortTrunkFailure NOTIFICATION-TYPE
    OBJECTS   { ifIndex, actorkey, partnerkey}
	STATUS		current
	DESCRIPTION
	   "Send this trap when one port is not able to be aggregated
	    due to duplex-mode of the port. "
	::= { es2310qTrapEntry 124 }

es2310qGvrpStateDisabled NOTIFICATION-TYPE
	STATUS		current
	DESCRIPTION
	   "Send this trap when the operational state of GVRP is from enabled to disabled. "
	::= { es2310qTrapEntry 140 }

es2310qGvrpStateEnabled NOTIFICATION-TYPE
	STATUS		current
	DESCRIPTION
	   "Send this trap when the operational state of LACP is from disabled to enabled. "
	::= { es2310qTrapEntry 141 }

es2310qVlanPortBaseEnabled NOTIFICATION-TYPE
	STATUS		current
	DESCRIPTION
	   "Send this trap when the operational state of vlan is changed to port-based vlan."
	::= { es2310qTrapEntry 151 }

es2310qVlanTagBaseEnabled NOTIFICATION-TYPE
	STATUS		current
	DESCRIPTION
	   "Send this trap when the operational state of vlan is changed to tag-based vlan."
	::= { es2310qTrapEntry 152 }

es2310qVlanMetroBaseEnabled NOTIFICATION-TYPE
	STATUS		current
	DESCRIPTION
	   "Send this trap when the operational state of vlan is changed to metro-based vlan."
	::= { es2310qTrapEntry 153 }

es2310qUserLogin NOTIFICATION-TYPE
    OBJECTS   {username}
	STATUS		current
	DESCRIPTION
	   "Send this trap when one user logins the system."
	::= { es2310qTrapEntry 200 }

es2310qUserLogout NOTIFICATION-TYPE
    OBJECTS   {username}
	STATUS		current
	DESCRIPTION
	   "Send this trap when one user logouts the system."
	::= { es2310qTrapEntry 201 }

es2310qTrapVariable	OBJECT IDENTIFIER ::= { es2310qProduces 21 }

username OBJECT-TYPE
    SYNTAX      DisplayString
	MAX-ACCESS  read-only
	STATUS      current
	DESCRIPTION
	    "System account name."
	::= { es2310qTrapVariable 1 }

groupId OBJECT-TYPE
    SYNTAX      INTEGER(1..8)
	MAX-ACCESS  read-only
	STATUS      current
	DESCRIPTION
	    "The Trunk group ID of LACP."
	::= { es2310qTrapVariable 2 }

actorkey OBJECT-TYPE
    SYNTAX	INTEGER(1..2147483647)
	MAX-ACCESS  read-only
	STATUS      current
	DESCRIPTION
	    "The actor key information for LACP."
	::= { es2310qTrapVariable 3 }

partnerkey OBJECT-TYPE
    SYNTAX	INTEGER(1..2147483647)
	MAX-ACCESS  read-only
	STATUS      current
	DESCRIPTION
	    "The partner key information for LACP."
	::= { es2310qTrapVariable 4 }

uplink OBJECT-TYPE
    SYNTAX	DisplayString
	MAX-ACCESS  read-only
	STATUS      current
	DESCRIPTION
	    "Uplink port(s) in the metro-mode vlan."
	::= { es2310qTrapVariable 5 }

END
