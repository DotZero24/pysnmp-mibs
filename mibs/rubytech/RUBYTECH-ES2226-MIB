RUBYTECH-ES2226-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    MacAddress         FROM SNMPv2-TC
    ifIndex    FROM RFC1213-MIB;

-- @ENTERPRISE-SECTION-START
rubytech MODULE-IDENTITY
    LAST-UPDATED "200709190000Z"
        ORGANIZATION "Ruby Tech Corp."
        CONTACT-INFO
            "2F, No.7, Lane 50, Nan Kang Road, Sec.3, Taipei, Taiwan
                 Email: rubytech@mail.rubytech.com.tw
                 TEL: 886-2-2785-3961
                 FAX: 886-2-2786-3012"
        DESCRIPTION
                "The MIB module is for Ruby Tech."
        ::= { enterprises 5205 }

switch               OBJECT IDENTIFIER ::= { rubytech 2 }

es2226ProductID         OBJECT IDENTIFIER ::= { switch 31 }
-- @ENTERPRISE-SECTION-END

es2226Produces            OBJECT IDENTIFIER ::= { es2226ProductID 1 }

es2226System            OBJECT IDENTIFIER ::= { es2226Produces 1 }

es2226CommonSys             OBJECT IDENTIFIER ::= { es2226System 1 }

es2226Reboot OBJECT-TYPE
    SYNTAX      INTEGER(0|1|2)
    MAX-ACCESS      read-write
    STATUS      current
    DESCRIPTION
        "Reboot the system. Get this OID always return zero.
            0 - do nothing
            1 - Reboot without saving start
            2 - Reboot with saving start"
    ::= { es2226CommonSys 1 }

es2226BiosVsersion  OBJECT-TYPE
    SYNTAX      DisplayString
    MAX-ACCESS      read-only
    STATUS      current
    DESCRIPTION
        "Get the BIOS version of the system."
    ::= { es2226CommonSys 2 }

es2226FirmwareVersion   OBJECT-TYPE
    SYNTAX      DisplayString
    MAX-ACCESS      read-only
    STATUS      current
    DESCRIPTION
        "Get the firmware version of the system."
    ::= { es2226CommonSys 3 }

es2226HardwareVersion   OBJECT-TYPE
    SYNTAX      DisplayString
    MAX-ACCESS      read-only
    STATUS      current
    DESCRIPTION
        "Get the hardware version of the system."
    ::= { es2226CommonSys 4 }

es2226MechanicalVersion OBJECT-TYPE
    SYNTAX      DisplayString
    MAX-ACCESS      read-only
    STATUS      current
    DESCRIPTION
        "Get the mechanical version of the system."
    ::= { es2226CommonSys 5 }

es2226SerialNumber  OBJECT-TYPE
    SYNTAX      DisplayString
    MAX-ACCESS      read-only
    STATUS      current
    DESCRIPTION
        "Get the Serial number of the system."
    ::= { es2226CommonSys 6 }

es2226HostMacAddress    OBJECT-TYPE
    SYNTAX      DisplayString
    MAX-ACCESS      read-only
    STATUS      current
    DESCRIPTION
        "Get the MAC address of the system."
    ::= { es2226CommonSys 7 }

es2226DevicePort    OBJECT-TYPE
    SYNTAX      DisplayString
    MAX-ACCESS      read-only
    STATUS      current
    DESCRIPTION
        "Get the quantity of ports that this system owns now."
    ::= { es2226CommonSys 8 }

es2226RamSize  OBJECT-TYPE
    SYNTAX      DisplayString
    MAX-ACCESS      read-only
    STATUS      current
    DESCRIPTION
        "Get the RAM size of the system."
    ::= { es2226CommonSys 9 }

es2226FlashSize  OBJECT-TYPE
    SYNTAX      DisplayString
    MAX-ACCESS      read-only
    STATUS      current
    DESCRIPTION
        "Get the flash size of the system."
    ::= { es2226CommonSys 10 }

es2226CPULoad  OBJECT-TYPE
    SYNTAX      DisplayString
    MAX-ACCESS      read-only
    STATUS      current
    DESCRIPTION
        "Get the CPU load of the system."
    ::= { es2226CommonSys 11 }

es2226IP            OBJECT IDENTIFIER ::= { es2226System 2 }

es2226DhcpSetting OBJECT-TYPE
    SYNTAX          INTEGER(0|1)
    MAX-ACCESS          read-write
    STATUS          current
    DESCRIPTION
        "Get/Set DHCP status of the system.
            0 - DHCP disable
            1 - DHCP enable
            When DHCP Relay is already running. Please disable DHCP Relay first, and then enable DHCP again."
    ::= { es2226IP 1 }

es2226IPAddress OBJECT-TYPE
    SYNTAX      IpAddress
    MAX-ACCESS      read-write
    STATUS      current
    DESCRIPTION
        "Get/Set the IP address of the system.
         You can't set this OID if DHCP status is enabled."
    ::= { es2226IP 2 }

es2226NetMask OBJECT-TYPE
    SYNTAX      IpAddress
    MAX-ACCESS      read-write
    STATUS      current
    DESCRIPTION
        "Get/Set the subnet mask of the system.
         You can't set this OID if DHCP status is enabled."
    ::= { es2226IP 3 }

es2226DefaultGateway OBJECT-TYPE
    SYNTAX      IpAddress
    MAX-ACCESS      read-write
    STATUS      current
    DESCRIPTION
        "Get/Set the default gateway of the system.
         You can't set this OID if DHCP status is enabled."
    ::= { es2226IP 4 }

es2226DnsSetting OBJECT-TYPE
    SYNTAX      INTEGER(0|1)
    MAX-ACCESS      read-write
    STATUS      current
    DESCRIPTION
        "Get/Set the source of DNS server.
         You can't set this OID if DHCP status is disabled.
            0 - manual, the DNS server is from manual setting
            1 - Auto, the DNS server is assigned by DHCP server."
    ::= { es2226IP 5 }

es2226DnsServer OBJECT-TYPE
    SYNTAX      IpAddress
    MAX-ACCESS      read-write
    STATUS      current
    DESCRIPTION
        "Get/Set the DNS server of the system."
    ::= { es2226IP 6 }

es2226Time              OBJECT IDENTIFIER ::= { es2226System 3 }

es2226SystemCurrentTime OBJECT-TYPE
    SYNTAX      DisplayString
    MAX-ACCESS      read-only
    STATUS      current
    DESCRIPTION
        "Get the current time of the system."
    ::= { es2226Time 1 }

es2226ManualTimeSetting OBJECT-TYPE
    SYNTAX      DisplayString
    MAX-ACCESS      read-write
    STATUS      current
    DESCRIPTION
        "Get/Set the system time of the device.
        The input format is 'Year/Month/Day/Hour/Minute/Second'.
        Ex: 2004/1/1/12/34/25 means 2004/1/1 - 12:24:25.
        Value range:
        Year    : 2000 - 2036,
        Mouth   : 1 - 12,
        Day     : 1 - 31,
        Hour    : 0 - 23,
        Minute  : 0 - 59,
        Sec     : 0 - 59."
    ::= { es2226Time 2 }

es2226NTPServer OBJECT-TYPE
    SYNTAX      DisplayString
    MAX-ACCESS      read-write
    STATUS      current
    DESCRIPTION
        "Get/Set the NTP Time Server. You can use the IP address or domain name."
    ::= { es2226Time 3 }

es2226NTPTimeZone OBJECT-TYPE
    SYNTAX      INTEGER(-12..13)
    MAX-ACCESS      read-write
    STATUS      current
    DESCRIPTION
        "Get/Set the NTP Time Zone.
        Value range is between -12 and 13
        -12 - GMT -12:00,
        -11 - GMT -11:00,
        -10 - GMT -10:00,
         -9 - GMT -09:00,
         -8 - GMT -08:00,
         -7 - GMT -07:00,
         -6 - GMT -06:00,
         -5 - GMT -05:00,
         -4 - GMT -04:00,
         -3 - GMT -03:00,
         -2 - GMT -02:00,
         -1 - GMT -01:00,
          0 - GMT +00:00,
          1 - GMT +01:00,
          2 - GMT +02:00,
          3 - GMT +03:00,
          4 - GMT +04:00,
          5 - GMT +05:00,
          6 - GMT +06:00,
          7 - GMT +07:00,
          8 - GMT +08:00,
          9 - GMT +09:00,
         10 - GMT +10:00,
         11 - GMT +11:00,
         12 - GMT +12:00,
         13 - GMT +13:00. "
    ::= { es2226Time 4 }

es2226NTPTimeSync OBJECT-TYPE
    SYNTAX      INTEGER(0|1)
    MAX-ACCESS      read-write
    STATUS      current
    DESCRIPTION
        "Sync time from NTP Server. Get this OID always return zero.
        Set the Time Server and Time Zone before doing time sync.
        Notice that time server must be correct!
        Value range (1|0):
        1 - Sync.
        0 - do nothing."
    ::= { es2226Time 5 }

es2226DaylightSavingTime OBJECT-TYPE
    SYNTAX      INTEGER(-5..5)
    MAX-ACCESS      read-write
    STATUS      current
    DESCRIPTION
        "Get/Set the daylight saving time.
        Value range is between -5 and 5. Unit: hour. "
    ::= { es2226Time 6 }

es2226DaylightStartTime OBJECT-TYPE
    SYNTAX      DisplayString
    MAX-ACCESS      read-write
    STATUS      current
    DESCRIPTION
        "Get/Set the Start time of Daylight Saving.
        The input format is 'MM/DD/HH',
        and daylight saving start month can't equal end month.
        Example: month/day/hour   10/01/00
        Month: 01~12, day: 01~31, hour: 00~23."
    ::= { es2226Time 7 }

es2226DaylightEndTime OBJECT-TYPE
    SYNTAX      DisplayString
    MAX-ACCESS      read-write
    STATUS      current
    DESCRIPTION
        "Get/Set the End time of Daylight Saving.
        The input format is 'MM/DD/HH',
        and daylight saving start month can't equal end month.
        Example: month/day/hour   04/01/00
        Month: 01~12, day: 01~31, hour: 00~23."
    ::= { es2226Time 8 }


es2226Account               OBJECT IDENTIFIER ::= { es2226System 4 }

es2226AccountNumber OBJECT-TYPE
    SYNTAX      INTEGER(1..5)
    MAX-ACCESS      read-only
    STATUS      current
    DESCRIPTION
        "Get the current account number(s) of the system."
    ::= { es2226Account 1 }

es2226AccountTable  OBJECT-TYPE
    SYNTAX      SEQUENCE OF ES2226AccountEntry
    MAX-ACCESS  not-accessible
    STATUS      current
    DESCRIPTION
        "This is a list of es2226AccountEntry. The numbers of entries are given by
        the value of es2226AccountNumber."
    ::= { es2226Account 2 }

es2226AccountEntry  OBJECT-TYPE
    SYNTAX      ES2226AccountEntry
    MAX-ACCESS      not-accessible
    STATUS      current
    DESCRIPTION
        "This is the Entry(s) for account information."
    INDEX {es2226AccountIndex}
    ::= { es2226AccountTable 1 }

ES2226AccountEntry ::=
SEQUENCE {
    es2226AccountIndex          INTEGER,
    es2226AccountAuthorization  DisplayString,
    es2226AccountName             DisplayString,
    es2226AccountPassword         DisplayString
}

es2226AccountIndex  OBJECT-TYPE
    SYNTAX      INTEGER(1..5)
    MAX-ACCESS      read-only
    STATUS      current
    DESCRIPTION
        "This is the index of the account entry."
    ::= { es2226AccountEntry 1 }

es2226AccountAuthorization  OBJECT-TYPE
    SYNTAX      DisplayString
    MAX-ACCESS      read-only
    STATUS      current
    DESCRIPTION
        "This is the authorization of the account entry."
    ::= { es2226AccountEntry 2 }

es2226AccountName   OBJECT-TYPE
    SYNTAX      DisplayString
    MAX-ACCESS      read-write
    STATUS      current
    DESCRIPTION
        "This is the username of the account entry."
    ::= { es2226AccountEntry 3 }

es2226AccountPassword   OBJECT-TYPE
    SYNTAX      DisplayString
    MAX-ACCESS      read-write
    STATUS      current
    DESCRIPTION
        "This is the password of the account entry. The return value is always '********'."
    ::= { es2226AccountEntry 4 }

es2226AccountAddName OBJECT-TYPE
    SYNTAX      DisplayString
    MAX-ACCESS      read-write
    STATUS      current
    DESCRIPTION
        "This is the account name for adding operation."
    ::= { es2226Account 3 }

es2226AccountAddPassword OBJECT-TYPE
    SYNTAX      DisplayString
    MAX-ACCESS      read-write
    STATUS      current
    DESCRIPTION
        "This is the account password for adding operation. The return value is always '********'."
    ::= { es2226Account 4 }

es2226DoAccountAdd OBJECT-TYPE
    SYNTAX      INTEGER(0|1)
    MAX-ACCESS      read-write
    STATUS      current
    DESCRIPTION
        "Add account name. OID es2226AccountAddName and es2226AccountAddPassword must be
        filled first. Get this OID always return zero.
            1 - Add account.
            0 - do nothing."
    ::= { es2226Account 5 }

es2226AccountDel    OBJECT-TYPE
    SYNTAX      INTEGER(2..5)
    MAX-ACCESS      read-write
    STATUS      current
    DESCRIPTION
        "Delete account. The value is valid es2226AccountIndex(Can't delete administrator)."
    ::= { es2226Account 6 }


es2226TrapHost              OBJECT IDENTIFIER ::= { es2226Produces 2 }

es2226TrapBootDelayTime OBJECT-TYPE
    SYNTAX      INTEGER(0..120)
    MAX-ACCESS      read-write
    STATUS      current
    DESCRIPTION
        "Get/Set trap boot delay time in second. Default: 0"
    ::= { es2226TrapHost 1 }

es2226TrapHostTable OBJECT-TYPE
    SYNTAX      SEQUENCE OF ES2226TrapHostEntry
    MAX-ACCESS  not-accessible
    STATUS      current
    DESCRIPTION
        "A list of trap host entry. The numbers of entries are given by the value of es2226TrapHostNumber."
    ::= { es2226TrapHost 2 }

es2226TrapHostEntry OBJECT-TYPE
    SYNTAX      ES2226TrapHostEntry
    MAX-ACCESS      not-accessible
    STATUS      current
    DESCRIPTION
        "This is the entry information for trap host."
    INDEX {es2226TrapHostIndex}
    ::= { es2226TrapHostTable 1 }

ES2226TrapHostEntry ::=
SEQUENCE {
    es2226TrapHostIndex         INTEGER,
    es2226TrapHostVersion       INTEGER,
    es2226TrapHostIP            IpAddress,
    es2226TrapHostPort            INTEGER,
    es2226TrapHostCommunity       DisplayString,
    es2226TrapHostSecurity         INTEGER,
    es2226TrapHostAuthPtc          DisplayString,
    es2226TrapHostAuthPassword     DisplayString,
    es2226TrapHostPrivPtc          DisplayString,
    es2226TrapHostPrivPassword     DisplayString,
    es2226TrapHostCurrentMode     INTEGER
}

es2226TrapHostIndex OBJECT-TYPE
    SYNTAX      INTEGER(1..6)
    MAX-ACCESS      read-only
    STATUS      current
    DESCRIPTION
        "The index of the trap host entry."
    ::= { es2226TrapHostEntry 1 }

es2226TrapHostVersion OBJECT-TYPE
    SYNTAX      INTEGER(1..3)
    MAX-ACCESS      read-write
    STATUS      current
    DESCRIPTION
        "The version of the Trap PDU. Version :1(SNMPv1), 2(SNMPv2c), 3(SNMPv3)"
    ::= { es2226TrapHostEntry 2 }

es2226TrapHostIP    OBJECT-TYPE
    SYNTAX      IpAddress
    MAX-ACCESS      read-write
    STATUS      current
    DESCRIPTION
        "This is the IP of the trap host."
    ::= { es2226TrapHostEntry 3 }


es2226TrapHostPort  OBJECT-TYPE
    SYNTAX      INTEGER(1..65535)
    MAX-ACCESS      read-write
    STATUS      current
    DESCRIPTION
        "This is the receiving-port number of the trap host."
    ::= { es2226TrapHostEntry 4 }


es2226TrapHostCommunity OBJECT-TYPE
    SYNTAX      DisplayString
    MAX-ACCESS      read-write
    STATUS      current
    DESCRIPTION
        "The community/security name for the trap PDU."
    ::= { es2226TrapHostEntry 5 }

es2226TrapHostSecurity	OBJECT-TYPE
	SYNTAX		INTEGER(1..3)
	MAX-ACCESS	    read-write
	STATUS		current
	DESCRIPTION
		"The Security Level, NoAuthNoPriv, AuthNoPriv, and AuthPriv.
		 security : 1(NoAuthNoPriv), 2(AuthNoPriv), 3(AuthPriv)"
	::= { es2226TrapHostEntry 6 }

es2226TrapHostAuthPtc	OBJECT-TYPE
	SYNTAX		DisplayString
	MAX-ACCESS	    read-write
	STATUS		current
	DESCRIPTION
		"This is the Authentication Protocol, which is used in AuthNoPriv, and AuthPriv.
		 There are two Authentication Protocol can be choice, MD5 or SHA."
	::= { es2226TrapHostEntry 7 }

es2226TrapHostAuthPassword	OBJECT-TYPE
	SYNTAX		DisplayString
	MAX-ACCESS	    read-write
	STATUS		current
	DESCRIPTION
		"The password is Authentication Key.  The return value is always '********'.
		 This Key must be more then 8 characters.  If your Authentication Key is MD5,
		 then your Authentication Key could not be more then 32 characters. If your
		 Authentication Key is SHA, then your Authentication Key could not be more then
		 40 characters."
	::= { es2226TrapHostEntry 8 }

es2226TrapHostPrivPtc	OBJECT-TYPE
	SYNTAX		DisplayString
	MAX-ACCESS	    read-only
	STATUS		current
	DESCRIPTION
		"This is the Privacy Procol, which is used in AuthPriv."
	::= { es2226TrapHostEntry 9 }

es2226TrapHostPrivPassword	OBJECT-TYPE
	SYNTAX		DisplayString
	MAX-ACCESS	    read-write
	STATUS		current
	DESCRIPTION
		"The password is Privacy Key.  The return value is always '********'.  This Key
		must be more than 8 characters, and less than 40 characters."
	::= { es2226TrapHostEntry 10 }

es2226TrapHostCurrentMode OBJECT-TYPE
	SYNTAX      INTEGER(0..2)
	MAX-ACCESS	    read-write
	STATUS		current
	DESCRIPTION
  		"0:Active mode, 1:Edit mode, 2:Do edit."
	::= { es2226TrapHostEntry 11 }


es2226Alarm             OBJECT IDENTIFIER ::= { es2226Produces 3 }

es2226Event             OBJECT IDENTIFIER ::= { es2226Alarm 1 }

es2226EventNumber OBJECT-TYPE
    SYNTAX      INTEGER(1..2147483647)
    MAX-ACCESS      read-only
    STATUS      current
    DESCRIPTION
        "Get the total number of alarm events."
    ::= { es2226Event 1 }

es2226EventTable    OBJECT-TYPE
    SYNTAX      SEQUENCE OF ES2226EventEntry
    MAX-ACCESS  not-accessible
    STATUS      current
    DESCRIPTION
        "This is a list of alarm event entry. The numbers of entries are given by the value of es2226EventNumber."
    ::= { es2226Event 2 }

es2226EventEntry    OBJECT-TYPE
    SYNTAX      ES2226EventEntry
    MAX-ACCESS      not-accessible
    STATUS      current
    DESCRIPTION
        "This is the entry information for alarm event."
    INDEX {es2226EventIndex}
    ::= { es2226EventTable 1 }

ES2226EventEntry ::=
SEQUENCE {
    es2226EventIndex            INTEGER,
    es2226EventName             DisplayString,
    es2226EventSendEmail      INTEGER,
    es2226EventSendTrap       INTEGER
}

es2226EventIndex    OBJECT-TYPE
    SYNTAX      INTEGER(1..2147483647)
    MAX-ACCESS      read-only
    STATUS      current
    DESCRIPTION
        "This is the index of the alarm event entry."
    ::= { es2226EventEntry 1 }

es2226EventName OBJECT-TYPE
    SYNTAX      DisplayString
    MAX-ACCESS      read-only
    STATUS      current
    DESCRIPTION
        "This is the alarm event name."
    ::= { es2226EventEntry 2 }

es2226EventSendEmail    OBJECT-TYPE
    SYNTAX      INTEGER(0|1)
    MAX-ACCESS      read-write
    STATUS      current
    DESCRIPTION
        "Send email when alarm event is triggered."
    ::= { es2226EventEntry 3 }

es2226EventSendTrap OBJECT-TYPE
    SYNTAX      INTEGER(0|1)
    MAX-ACCESS      read-write
    STATUS      current
    DESCRIPTION
        "Send trap when alarm event is triggered."
    ::= { es2226EventEntry 4 }


es2226Email             OBJECT IDENTIFIER ::= { es2226Alarm 2 }

es2226EmailServer OBJECT-TYPE
    SYNTAX      DisplayString
    MAX-ACCESS      read-write
    STATUS      current
    DESCRIPTION
        "This is the SMTP server for alarm event."
    ::= { es2226Email 1 }

es2226EmailUsername OBJECT-TYPE
    SYNTAX      DisplayString
    MAX-ACCESS      read-write
    STATUS      current
    DESCRIPTION
        "This is the Username of SMTP server."
    ::= { es2226Email 2 }

es2226EmailPassword OBJECT-TYPE
    SYNTAX      DisplayString
    MAX-ACCESS      read-write
    STATUS      current
    DESCRIPTION
        "This is the User Password of SMTP server."
    ::= { es2226Email 3 }

es2226EmailSender OBJECT-TYPE
	SYNTAX      DisplayString
	MAX-ACCESS	    read-write
	STATUS		current
	DESCRIPTION
		"This is the Sender of SMTP server."
	::= { es2226Email 4 }

es2226EmailReturnPath OBJECT-TYPE
	SYNTAX      DisplayString
	MAX-ACCESS	    read-write
	STATUS		current
	DESCRIPTION
		"This is the return path of mail."
	::= { es2226Email 5 }

es2226EmailUserNumber OBJECT-TYPE
    SYNTAX      INTEGER(1..6)
    MAX-ACCESS      read-only
    STATUS      current
    DESCRIPTION
        "The number of the email users that you want to send the alarm notification."
    ::= { es2226Email 6 }

es2226EmailUserTable    OBJECT-TYPE
    SYNTAX      SEQUENCE OF ES2226EmailUserEntry
    MAX-ACCESS  not-accessible
    STATUS      current
    DESCRIPTION
        "This is a list of email user entry. The numbers of entries are given by the value of es2226EmailUserNumber."
    ::= { es2226Email 7 }

es2226EmailUserEntry    OBJECT-TYPE
    SYNTAX      ES2226EmailUserEntry
    MAX-ACCESS      not-accessible
    STATUS      current
    DESCRIPTION
        "This is the Entry information for email user entry."
    INDEX {es2226EmailUserIndex}
    ::= { es2226EmailUserTable 1 }

ES2226EmailUserEntry ::=
SEQUENCE {
    es2226EmailUserIndex            INTEGER,
    es2226EmailUserAddress          DisplayString
}

es2226EmailUserIndex    OBJECT-TYPE
    SYNTAX      INTEGER(1..6)
    MAX-ACCESS      read-only
    STATUS      current
    DESCRIPTION
        "This is the index of the email user entry."
    ::= { es2226EmailUserEntry 1 }

es2226EmailUserAddress  OBJECT-TYPE
    SYNTAX      DisplayString
    MAX-ACCESS      read-write
    STATUS      current
    DESCRIPTION
        "This is the email address of the email user entry."
    ::= { es2226EmailUserEntry 2 }

es2226Tftp              OBJECT IDENTIFIER ::= { es2226Produces 4 }

es2226TftpServer OBJECT-TYPE
    SYNTAX      IpAddress
    MAX-ACCESS      read-write
    STATUS      current
    DESCRIPTION
        "Get/Set the tftp server."
    ::= { es2226Tftp 1 }


es2226Configuration             OBJECT IDENTIFIER ::= { es2226Produces 5 }

es2226SaveRestore               OBJECT IDENTIFIER ::= { es2226Configuration 1 }

es2226SaveStart OBJECT-TYPE
    SYNTAX      INTEGER(0|1)
    MAX-ACCESS      read-write
    STATUS      current
    DESCRIPTION
        "Save current configuration into flash memory (Save as Start Configuration).
         if the account/group is generating, please wait.
        Get this OID always return zero.
            1 - Save.
            0 - do nothing. "
    ::= { es2226SaveRestore 1 }

es2226SaveUser OBJECT-TYPE
    SYNTAX      INTEGER(0|1)
    MAX-ACCESS      read-write
    STATUS      current
    DESCRIPTION
        "Save current configuration into flash memory (Save as User Configuration).
         if the account/group is generating, please wait.
        Get this OID always return zero.
            1 - Save.
            0 - do nothing. "
    ::= { es2226SaveRestore 2 }

es2226RestoreDefault OBJECT-TYPE
    SYNTAX      INTEGER(0|1|2)
    MAX-ACCESS      read-write
    STATUS      current
    DESCRIPTION
        "Restore factory default configuration.
         if the account/group is generating, please wait.
        Get this OID always return zero.
            2 - Restore default included default ip address.
        1 - Restore default without changing current ip address.
            0 - do nothing. "
    ::= { es2226SaveRestore 3 }

es2226RestoreUser OBJECT-TYPE
    SYNTAX      INTEGER(0|1)
    MAX-ACCESS      read-write
    STATUS      current
    DESCRIPTION
        "Restore user configuration.
         if the account/group is generating, please wait.
        Get this OID always return zero.
            1 - Restore.
            0 - do nothing. "
    ::= { es2226SaveRestore 4 }


es2226ConfigFile            OBJECT IDENTIFIER ::= { es2226Configuration 2 }

es2226ExportConfigName OBJECT-TYPE
    SYNTAX      DisplayString
    MAX-ACCESS      read-write
    STATUS      current
    DESCRIPTION
        "Get/Set the export file path and name."
    ::= { es2226ConfigFile 1 }

es2226DoExportConfig OBJECT-TYPE
    SYNTAX      INTEGER(1|2)
    MAX-ACCESS      read-write
    STATUS      current
    DESCRIPTION
        "Do export-config.
        Get this OID always return zero.
            1   -   Export start section.
            2   -   Export user-conf section."
    ::= { es2226ConfigFile 2 }

es2226ImportConfigName OBJECT-TYPE
    SYNTAX      DisplayString
    MAX-ACCESS      read-write
    STATUS      current
    DESCRIPTION
        "Get/Set the import file path and name."
    ::= { es2226ConfigFile 3 }

es2226DoImportConfig OBJECT-TYPE
    SYNTAX      INTEGER(1|2)
    MAX-ACCESS      read-write
    STATUS      current
    DESCRIPTION
        "Do import-config.
        Get this OID always return zero.
            1   -   Import start section.
            2   -   Import user-conf section."
    ::= { es2226ConfigFile 4 }

es2226Diagnostic            OBJECT IDENTIFIER ::= { es2226Produces 6 }

es2226EEPROMTest OBJECT-TYPE
    SYNTAX      DisplayString
    MAX-ACCESS      read-only
    STATUS      current
    DESCRIPTION
        "EEPROM access test."
    ::= { es2226Diagnostic 1 }

es2226UartTest OBJECT-TYPE
    SYNTAX      DisplayString
    MAX-ACCESS      read-only
    STATUS      current
    DESCRIPTION
        "UART access test."
    ::= { es2226Diagnostic 2 }

es2226DramTest OBJECT-TYPE
    SYNTAX      DisplayString
    MAX-ACCESS      read-only
    STATUS      current
    DESCRIPTION
        "DRAM access test."
    ::= { es2226Diagnostic 3 }

es2226FlashTest OBJECT-TYPE
    SYNTAX      DisplayString
    MAX-ACCESS      read-only
    STATUS      current
    DESCRIPTION
        "Flash memory access test."
    ::= { es2226Diagnostic 4 }

es2226InternalLoopbackTest OBJECT-TYPE
    SYNTAX      DisplayString
    MAX-ACCESS      read-only
    STATUS      current
    DESCRIPTION
        "Internal loop back test."
    ::= { es2226Diagnostic 5 }

es2226ExternalLoopbackTest OBJECT-TYPE
    SYNTAX      DisplayString
    MAX-ACCESS      read-only
    STATUS      current
    DESCRIPTION
        "External loop back test."
    ::= { es2226Diagnostic 6 }

es2226PingTest OBJECT-TYPE
    SYNTAX      DisplayString
    MAX-ACCESS      read-write
    STATUS      current
    DESCRIPTION
        "Set the host address that you want to ping and the system will return the test result."
    ::= { es2226Diagnostic 7 }

es2226Log               OBJECT IDENTIFIER ::= { es2226Produces 7 }

es2226ClearLog OBJECT-TYPE
    SYNTAX      INTEGER(0|1)
    MAX-ACCESS      read-write
    STATUS      current
    DESCRIPTION
        "Clear system log.
        Get this OID always return zero.
            1 - Clear log.
            0 - do nothing. "
    ::= { es2226Log 1 }

es2226UploadLog OBJECT-TYPE
    SYNTAX      INTEGER(0|1)
    MAX-ACCESS      read-write
    STATUS      current
    DESCRIPTION
        "Upload current system log. Set the correct tftp server first.
        The format of log file is 'ModelName_SerialNumbuer_YYMMDD_HHMM'.
        Get this OID always return zero.
            1 - Upload log
            0 - do nothing. "
    ::= { es2226Log 2 }

es2226AutoUploadLogState OBJECT-TYPE
    SYNTAX      INTEGER(0|1)
    MAX-ACCESS      read-write
    STATUS      current
    DESCRIPTION
        "Enable auto-upload log function. Set the correct tftp server first.
        The format of log file is 'ModelName_SerialNumbuer_YYMMDD_HHMM'.
        Get this OID always return zero.
            1 - Enable auto-upload
            0 - do nothing. "
    ::= { es2226Log 3 }

es2226LogNumber OBJECT-TYPE
    SYNTAX      INTEGER(0..120)
    MAX-ACCESS      read-only
    STATUS      current
    DESCRIPTION
        "Get the number of current system log."
    ::= { es2226Log 4 }

es2226LogTable  OBJECT-TYPE
    SYNTAX      SEQUENCE OF ES2226LogEntry
    MAX-ACCESS  not-accessible
    STATUS      current
    DESCRIPTION
        "This is a list of log entry. The numbers of entries are given by the value of es2226LogNumber."
    ::= { es2226Log 5 }

es2226LogEntry  OBJECT-TYPE
    SYNTAX      ES2226LogEntry
    MAX-ACCESS      not-accessible
    STATUS      current
    DESCRIPTION
        "This is the Entry information for system log."
    INDEX {es2226LogIndex}
    ::= { es2226LogTable 1 }

ES2226LogEntry ::=
SEQUENCE {
    es2226LogIndex          INTEGER,
    es2226LogEvent              DisplayString
}

es2226LogIndex  OBJECT-TYPE
    SYNTAX      INTEGER(1..120)
    MAX-ACCESS      read-only
    STATUS      current
    DESCRIPTION
        "This is the index of the log entry."
    ::= { es2226LogEntry 1 }

es2226LogEvent  OBJECT-TYPE
    SYNTAX      DisplayString
    MAX-ACCESS      read-only
    STATUS      current
    DESCRIPTION
        "This is the detail information of the log entry."
    ::= { es2226LogEntry 2 }

es2226Firmware              OBJECT IDENTIFIER ::= { es2226Produces 8 }

es2226FirmwareFileName OBJECT-TYPE
    SYNTAX      DisplayString
    MAX-ACCESS      read-write
    STATUS      current
    DESCRIPTION
        "Get/Set the path and filename for firmware upgrading."
    ::= { es2226Firmware 1 }

es2226DoFirmwareUpgrade OBJECT-TYPE
    SYNTAX      INTEGER(0|1)
    MAX-ACCESS      read-write
    STATUS      current
    DESCRIPTION
        "Do firmware upgrade. Get this OID always return zero.
            1 - Do firmware upgrade.
            0 - do nothing."
    ::= { es2226Firmware 2 }


es2226Port              OBJECT IDENTIFIER ::= { es2226Produces 9 }

es2226PortStatus            OBJECT IDENTIFIER ::= { es2226Port 1 }

es2226PortStatusNumber OBJECT-TYPE
    SYNTAX      INTEGER(1..2147483647)
    MAX-ACCESS      read-only
    STATUS      current
    DESCRIPTION
        "Get the number of port."
    ::= { es2226PortStatus 1 }

es2226PortStatusTable   OBJECT-TYPE
    SYNTAX      SEQUENCE OF ES2226PortStatusEntry
    MAX-ACCESS  not-accessible
    STATUS      current
    DESCRIPTION
        "This is a list of port status entry. The numbers of entries are given by the value of es2226PortStatusNumber."
    ::= { es2226PortStatus 2 }

es2226PortStatusEntry   OBJECT-TYPE
    SYNTAX      ES2226PortStatusEntry
    MAX-ACCESS      not-accessible
    STATUS      current
    DESCRIPTION
        "This is the entry(s) for port status information."
    INDEX {es2226PortStatusIndex}
    ::= { es2226PortStatusTable 1 }

ES2226PortStatusEntry ::=
SEQUENCE {
    es2226PortStatusIndex           INTEGER,
    es2226PortStatusMedia          DisplayString,
    es2226PortStatusLink           DisplayString,
    es2226PortStatusPortState      DisplayString,
    es2226PortStatusAutoNego       DisplayString,
    es2226PortStatusSpdDpx         DisplayString,
    es2226PortStatusRxPause        DisplayString,
    es2226PortStatusTxPause        DisplayString,
    es2226PortStatusDescription     DisplayString
}

es2226PortStatusIndex   OBJECT-TYPE
    SYNTAX      INTEGER(1..2147483647)
    MAX-ACCESS      read-only
    STATUS      current
    DESCRIPTION
        "This is the index of the port status entry."
    ::= { es2226PortStatusEntry 1 }

es2226PortStatusMedia   OBJECT-TYPE
    SYNTAX      DisplayString
    MAX-ACCESS      read-only
    STATUS      current
    DESCRIPTION
        "This is the port media type of the port status entry."
    ::= { es2226PortStatusEntry 2 }

es2226PortStatusLink    OBJECT-TYPE
    SYNTAX      DisplayString
    MAX-ACCESS      read-only
    STATUS      current
    DESCRIPTION
        "This is the port link of the port status entry."
    ::= { es2226PortStatusEntry 3 }

es2226PortStatusPortState   OBJECT-TYPE
    SYNTAX      DisplayString
    MAX-ACCESS      read-only
    STATUS      current
    DESCRIPTION
        "This is the port state of the port status entry."
    ::= { es2226PortStatusEntry 4 }

es2226PortStatusAutoNego    OBJECT-TYPE
    SYNTAX      DisplayString
    MAX-ACCESS      read-only
    STATUS      current
    DESCRIPTION
        "This is the auto negotiation of the port status entry."
    ::= { es2226PortStatusEntry 5 }

es2226PortStatusSpdDpx  OBJECT-TYPE
    SYNTAX      DisplayString
    MAX-ACCESS      read-only
    STATUS      current
    DESCRIPTION
        "This is the speed/duplex of the port status entry."
    ::= { es2226PortStatusEntry 6 }

es2226PortStatusRxPause     OBJECT-TYPE
    SYNTAX      DisplayString
    MAX-ACCESS      read-only
    STATUS      current
    DESCRIPTION
        "The Rx Pause of the port status entry."
    ::= { es2226PortStatusEntry 7 }

es2226PortStatusTxPause     OBJECT-TYPE
    SYNTAX      DisplayString
    MAX-ACCESS      read-only
    STATUS      current
    DESCRIPTION
        "The Tx Pause of the port status entry."
    ::= { es2226PortStatusEntry 8 }

es2226PortStatusDescription  OBJECT-TYPE
    SYNTAX      DisplayString
    MAX-ACCESS  read-only
    STATUS      current
    DESCRIPTION
        "This is the description of port."
    ::= { es2226PortStatusEntry 9 }

es2226PortConf              OBJECT IDENTIFIER ::= { es2226Port 2 }

es2226PortConfNumber OBJECT-TYPE
    SYNTAX      INTEGER(1..2147483647)
    MAX-ACCESS      read-only
    STATUS      current
    DESCRIPTION
        "Get the number of port configuration."
    ::= { es2226PortConf 1 }

es2226PortConfTable OBJECT-TYPE
    SYNTAX      SEQUENCE OF ES2226PortConfEntry
    MAX-ACCESS  not-accessible
    STATUS      current
    DESCRIPTION
        "This is a list of port configuration entry. The numbers of entries are given by the value of es2226PortConfNumber."
    ::= { es2226PortConf 2 }

es2226PortConfEntry OBJECT-TYPE
    SYNTAX      ES2226PortConfEntry
    MAX-ACCESS      not-accessible
    STATUS      current
    DESCRIPTION
        "This is the Entry(s) for port configuration information."
    INDEX {es2226PortConfIndex}
    ::= { es2226PortConfTable 1 }

ES2226PortConfEntry ::=
SEQUENCE {
    es2226PortConfIndex            INTEGER,
    es2226PortConfPortState        INTEGER,
    es2226PortConfSpdDpx           INTEGER,
    es2226PortConfFlwCtrl          INTEGER,
    es2226PortConfPowerSaving      INTEGER,
    es2226PortConfDescription      DisplayString
}

es2226PortConfIndex OBJECT-TYPE
    SYNTAX      INTEGER(1..2147483647)
    MAX-ACCESS      read-only
    STATUS      current
    DESCRIPTION
        "This is the index of the port configuration entry."
    ::= { es2226PortConfEntry 1 }

es2226PortConfPortState OBJECT-TYPE
    SYNTAX      INTEGER(0|1)
    MAX-ACCESS      read-write
    STATUS      current
    DESCRIPTION
        "This is the port state of the port configuration entry.
         0 - disabled.
         1 - enabled. "
    ::= { es2226PortConfEntry 2 }

es2226PortConfSpdDpx    OBJECT-TYPE
    SYNTAX      INTEGER(0..5)
    MAX-ACCESS      read-write
    STATUS      current
    DESCRIPTION
        "This is the speed/duplex of the port configuration entry. Only Port25 & Port26 can set 1G/Full.
         0 - auto.
         1 - 10M/Half.
         2 - 10M/Full.
         3 - 100M/Half.
         4 - 100M/Full.
         5 - 1G/Full.  "
    ::= { es2226PortConfEntry 3 }

es2226PortConfFlwCtrl   OBJECT-TYPE
    SYNTAX      INTEGER(0..1)
    MAX-ACCESS      read-write
    STATUS      current
    DESCRIPTION
        "This is the flow control of the port configuration entry.
         0 - disable
         1 - symmetric.
        "
    ::= { es2226PortConfEntry 4 }

es2226PortConfPowerSaving   OBJECT-TYPE
    SYNTAX      INTEGER(0|1)
    MAX-ACCESS  read-write
    STATUS      current
    DESCRIPTION
        "This is the power saving of the port configuration entry.
         0 - disable
         1 - enable."
    ::= { es2226PortConfEntry 5 }

es2226PortConfDescription   OBJECT-TYPE
    SYNTAX      DisplayString
    MAX-ACCESS  read-write
    STATUS      current
    DESCRIPTION
        "This is the description of port."
    ::= { es2226PortConfEntry 6 }

es2226PortBandwidth             OBJECT IDENTIFIER ::= { es2226Port 3 }

es2226PortBandwidthNumber   OBJECT-TYPE
    SYNTAX      INTEGER(1..2147483647)
    MAX-ACCESS      read-only
    STATUS      current
    DESCRIPTION
        "Get the number of port bandwidth number."
    ::= { es2226PortBandwidth 1 }

es2226PortBandwidthTable    OBJECT-TYPE
    SYNTAX      SEQUENCE OF ES2226PortBandwidthEntry
    MAX-ACCESS  not-accessible
    STATUS      current
    DESCRIPTION
        "A list of port bandwidth entry. The number of entries are given by the value of es2226PortBandwidthNumber."
    ::= { es2226PortBandwidth 2 }

es2226PortBandwidthEntry    OBJECT-TYPE
    SYNTAX      ES2226PortBandwidthEntry
    MAX-ACCESS      not-accessible
    STATUS      current
    DESCRIPTION
        "Entry(s) for port bandwidth informaion."
    INDEX {es2226PortBandwidthIndex}
    ::= { es2226PortBandwidthTable 1 }

ES2226PortBandwidthEntry ::=
SEQUENCE {
    es2226PortBandwidthIndex              INTEGER,
    es2226PortBandwidthIngressRate        INTEGER,
    es2226PortBandwidthEgressRate         INTEGER,
    es2226PortBandwidthStormType          INTEGER,
    es2226PortBandwidthStormRate          INTEGER
}

es2226PortBandwidthIndex    OBJECT-TYPE
    SYNTAX      INTEGER(1..26)
    MAX-ACCESS      read-only
    STATUS      current
    DESCRIPTION
        "The index of the port bandwidth entry."
    ::= { es2226PortBandwidthEntry 1 }

es2226PortBandwidthIngressRate  OBJECT-TYPE
    SYNTAX      INTEGER(64..1024000)
    MAX-ACCESS      read-write
    STATUS      current
    DESCRIPTION
        "The Ingress rate(64~1024000) of the Bandwidth configuration."
    ::= { es2226PortBandwidthEntry 2 }

es2226PortBandwidthEgressRate   OBJECT-TYPE
    SYNTAX      INTEGER(64..1024000)
    MAX-ACCESS      read-write
    STATUS      current
    DESCRIPTION
        "The Egress rate(64~1024000) of the Bandwidth configuration."
    ::= { es2226PortBandwidthEntry 3 }

es2226PortBandwidthStormType    OBJECT-TYPE
    SYNTAX      INTEGER(0..7)
    MAX-ACCESS      read-write
    STATUS      current
    DESCRIPTION
        "The storm type of the Bandwidth configuration.
         0 - Disable.
             1 - BC.
             2 - UC.
             3 - BC,UC.
             4 - MC.
             5 - BC,MC.
             6 - UC,MC.
             7 - BC,UC,MC."
    ::= { es2226PortBandwidthEntry 4 }

es2226PortBandwidthStormRate    OBJECT-TYPE
    SYNTAX      INTEGER(64..1024000)
    MAX-ACCESS      read-write
    STATUS      current
    DESCRIPTION
        "The storm rate(64~1024000) of the Bandwidth configuration."
    ::= { es2226PortBandwidthEntry 5 }

es2226PortSFPInfo               OBJECT IDENTIFIER ::= { es2226Port 4 }

es2226PortSFPInfoNumber OBJECT-TYPE
    SYNTAX      INTEGER(1..2147483647)
    MAX-ACCESS      read-only
    STATUS      current
    DESCRIPTION
        "Get the number of sfp info entry."
    ::= { es2226PortSFPInfo 1 }

es2226PortSFPInfoTable  OBJECT-TYPE
    SYNTAX      SEQUENCE OF ES2226PORTSFPInfoEntry
    MAX-ACCESS  not-accessible
    STATUS      current
    DESCRIPTION
        "A list of sfp info entry. The numbers of entries are given by the value of es2226PortSFPInfoNumber."
    ::= { es2226PortSFPInfo 2 }

es2226PortSFPInfoEntry  OBJECT-TYPE
    SYNTAX      ES2226PORTSFPInfoEntry
    MAX-ACCESS      not-accessible
    STATUS      current
    DESCRIPTION
        "Entry(s) for SFP information."
    INDEX {es2226PortSFPInfoIndex}
    ::= { es2226PortSFPInfoTable 1 }

ES2226PORTSFPInfoEntry ::=
SEQUENCE {
    es2226PortSFPInfoIndex      INTEGER,
    es2226PortSFPConnectorType  DisplayString,
    es2226PortSFPFiberType      DisplayString,
    es2226PortSFPWavelength     DisplayString,
    es2226PortSFPBaudRate       DisplayString,
    es2226PortSFPVendorOUI      DisplayString,
    es2226PortSFPVendorName     DisplayString,
    es2226PortSFPVendorPN       DisplayString,
    es2226PortSFPVendorRev      DisplayString,
    es2226PortSFPVendorSN       DisplayString,
    es2226PortSFPDateCode       DisplayString,
    es2226PortSFPTemperature    DisplayString,
    es2226PortSFPVcc            DisplayString,
    es2226PortSFPTxBias         DisplayString,
    es2226PortSFPTxPWR          DisplayString,
    es2226PortSFPRxPWR          DisplayString
}

es2226PortSFPInfoIndex  OBJECT-TYPE
    SYNTAX      INTEGER(1..2147483647)
    MAX-ACCESS      read-only
    STATUS      current
    DESCRIPTION
        "The index of the sfp info entry."
    ::= { es2226PortSFPInfoEntry 1 }

es2226PortSFPConnectorType  OBJECT-TYPE
    SYNTAX      DisplayString
    MAX-ACCESS      read-only
    STATUS      current
    DESCRIPTION
        "Get connector type of the sfp."
    ::= { es2226PortSFPInfoEntry 2 }

es2226PortSFPFiberType  OBJECT-TYPE
    SYNTAX      DisplayString
    MAX-ACCESS      read-only
    STATUS      current
    DESCRIPTION
        "Get fiber type of the sfp."
    ::= { es2226PortSFPInfoEntry 3 }

es2226PortSFPWavelength OBJECT-TYPE
    SYNTAX      DisplayString
    MAX-ACCESS      read-only
    STATUS      current
    DESCRIPTION
        "Get tx central wavelength of the sfp."
    ::= { es2226PortSFPInfoEntry 4 }

es2226PortSFPBaudRate   OBJECT-TYPE
    SYNTAX      DisplayString
    MAX-ACCESS      read-only
    STATUS      current
    DESCRIPTION
        "Get baud rate of the sfp."
    ::= { es2226PortSFPInfoEntry 5 }

es2226PortSFPVendorOUI  OBJECT-TYPE
    SYNTAX      DisplayString
    MAX-ACCESS      read-only
    STATUS      current
    DESCRIPTION
        "Get vendor OUI of the sfp."
    ::= { es2226PortSFPInfoEntry 6 }

es2226PortSFPVendorName OBJECT-TYPE
    SYNTAX      DisplayString
    MAX-ACCESS      read-only
    STATUS      current
    DESCRIPTION
        "Get vendor name of the sfp."
    ::= { es2226PortSFPInfoEntry 7 }

es2226PortSFPVendorPN   OBJECT-TYPE
    SYNTAX      DisplayString
    MAX-ACCESS      read-only
    STATUS      current
    DESCRIPTION
        "Get vendor part number of the sfp."
    ::= { es2226PortSFPInfoEntry 8 }

es2226PortSFPVendorRev  OBJECT-TYPE
    SYNTAX      DisplayString
    MAX-ACCESS      read-only
    STATUS      current
    DESCRIPTION
        "Get vendor revision number of the sfp."
    ::= { es2226PortSFPInfoEntry 9 }

es2226PortSFPVendorSN   OBJECT-TYPE
    SYNTAX      DisplayString
    MAX-ACCESS      read-only
    STATUS      current
    DESCRIPTION
        "Get vendor serial number of the sfp."
    ::= { es2226PortSFPInfoEntry 10 }

es2226PortSFPDateCode   OBJECT-TYPE
    SYNTAX      DisplayString
    MAX-ACCESS      read-only
    STATUS      current
    DESCRIPTION
        "Get data code of the sfp."
    ::= { es2226PortSFPInfoEntry 11 }

es2226PortSFPTemperature    OBJECT-TYPE
    SYNTAX      DisplayString
    MAX-ACCESS      read-only
    STATUS      current
    DESCRIPTION
        "Get current temperature of the sfp."
    ::= { es2226PortSFPInfoEntry 12 }

es2226PortSFPVcc    OBJECT-TYPE
    SYNTAX      DisplayString
    MAX-ACCESS      read-only
    STATUS      current
    DESCRIPTION
        "Get current internal supply voltage of the sfp."
    ::= { es2226PortSFPInfoEntry 13 }

es2226PortSFPTxBias OBJECT-TYPE
    SYNTAX      DisplayString
    MAX-ACCESS      read-only
    STATUS      current
    DESCRIPTION
        "Get current TX Bias of the sfp."
    ::= { es2226PortSFPInfoEntry 14 }

es2226PortSFPTxPWR  OBJECT-TYPE
    SYNTAX      DisplayString
    MAX-ACCESS      read-only
    STATUS      current
    DESCRIPTION
        "Get current TX output power of the sfp."
    ::= { es2226PortSFPInfoEntry 15 }

es2226PortSFPRxPWR  OBJECT-TYPE
    SYNTAX      DisplayString
    MAX-ACCESS      read-only
    STATUS      current
    DESCRIPTION
        "Get current Received Power of the sfp."
    ::= { es2226PortSFPInfoEntry 16 }

es2226LoopDetectedConf              OBJECT IDENTIFIER ::= { es2226Produces 10 }

es2226LoopDetectedNumber OBJECT-TYPE
    SYNTAX      INTEGER(1..2147483647)
    MAX-ACCESS      read-only
    STATUS      current
    DESCRIPTION
        "Get the number of loop detected entry."
    ::= { es2226LoopDetectedConf 1 }

es2226LoopDetectedTable OBJECT-TYPE
    SYNTAX      SEQUENCE OF ES2226LoopDetectedEntry
    MAX-ACCESS  not-accessible
    STATUS      current
    DESCRIPTION
        "This is a list of loop detected entry. The numbers of entries are given by the value of es2226LoopDetectedNumber."
    ::= { es2226LoopDetectedConf 2 }

es2226LoopDetectedEntry OBJECT-TYPE
    SYNTAX      ES2226LoopDetectedEntry
    MAX-ACCESS      not-accessible
    STATUS      current
    DESCRIPTION
        "Entry(s) for loop detected information."
    INDEX {es2226LoopDetectedfIndex}
    ::= { es2226LoopDetectedTable 1 }

ES2226LoopDetectedEntry ::=
SEQUENCE {
    es2226LoopDetectedfIndex           INTEGER,
    es2226LoopDetectedStateEbl         INTEGER,
    es2226LoopDetectedCurrentStatus    INTEGER,
    es2226LoopDetectedResumed          INTEGER
}

es2226LoopDetectedfIndex    OBJECT-TYPE
    SYNTAX      INTEGER(1..2147483647)
    MAX-ACCESS      read-only
    STATUS      current
    DESCRIPTION
        "This is the index of the loop detected entry."
    ::= { es2226LoopDetectedEntry 1 }

es2226LoopDetectedStateEbl  OBJECT-TYPE
    SYNTAX      INTEGER(0|1)
    MAX-ACCESS      read-write
    STATUS      current
    DESCRIPTION
        "The state of the loop detected entry.
         0 - disabled.
         1 - enabled. "
    ::= { es2226LoopDetectedEntry 2 }

es2226LoopDetectedCurrentStatus OBJECT-TYPE
    SYNTAX      INTEGER(0|1)
    MAX-ACCESS      read-only
    STATUS      current
    DESCRIPTION
        "The current status of the loop detected port.
         0 - unlocked
         1 - Locked due to the loop condition"
    ::= { es2226LoopDetectedEntry 3 }

es2226LoopDetectedResumed   OBJECT-TYPE
    SYNTAX      INTEGER(0|1)
    MAX-ACCESS      read-write
    STATUS      current
    DESCRIPTION
        "Unlock the port which is locked due to loop condition. Get this OID always return zero.
         1 - Unlock the port,
         0 - do nothing."
    ::= { es2226LoopDetectedEntry 4 }

es2226LoopDetectedAction OBJECT-TYPE
    SYNTAX      INTEGER(0|1)
    MAX-ACCESS      read-write
    STATUS      current
    DESCRIPTION
        "Set the corresponding action while loop is detected.
         1 - Lock the loop port,
         0 - do nothing."
    ::= { es2226LoopDetectedConf 3 }

es2226IpMacBind             OBJECT IDENTIFIER ::= { es2226Produces 11 }

es2226IpMacBindStatus           OBJECT IDENTIFIER ::= { es2226IpMacBind 1 }

es2226IpMacBindMode  OBJECT-TYPE
    SYNTAX      INTEGER(0|1)
    MAX-ACCESS      read-write
    STATUS      current
    DESCRIPTION
        "Set the IP-MAC Binding State.
         1 - Enable,
         0 - Disable."
    ::= { es2226IpMacBindStatus 1 }

es2226IpMacBindPort  OBJECT-TYPE
    SYNTAX      DisplayString
    MAX-ACCESS      read-write
    STATUS      current
    DESCRIPTION
        "Set the IP-MAC Binding Port.
         Syntax: 1,5-7, available from 1 to 26."
    ::= { es2226IpMacBindStatus 2 }

es2226IpMacBindCount  OBJECT-TYPE
    SYNTAX      INTEGER(0..2147483647)
    MAX-ACCESS      read-only
    STATUS      current
    DESCRIPTION
        "Get the current IP-MAC Binding user count."
    ::= { es2226IpMacBindStatus 3 }

es2226IpMacBindCreatStatus  OBJECT-TYPE
	SYNTAX  INTEGER(0|1)
	MAX-ACCESS     read-write
	STATUS  current
	DESCRIPTION
	"Create ip_mac_binding entry.
	0: none
	1: creat a entry."
 ::= { es2226IpMacBindStatus 4 }

es2226IpMacBindStatusTable  OBJECT-TYPE
    SYNTAX      SEQUENCE OF ES2226IpMacBindStatusEntry
    MAX-ACCESS  not-accessible
    STATUS      current
    DESCRIPTION
        " "
    ::= { es2226IpMacBindStatus 5 }

es2226IpMacBindStatusEntry  OBJECT-TYPE
    SYNTAX      ES2226IpMacBindStatusEntry
    MAX-ACCESS      not-accessible
    STATUS      current
    DESCRIPTION
        "Entry(s) for IP-MAC Binding Status."
    INDEX {es2226IpMacBindStatusIndex}
    ::= { es2226IpMacBindStatusTable 1 }

ES2226IpMacBindStatusEntry ::=
SEQUENCE {
    es2226IpMacBindStatusIndex      INTEGER,
    es2226IpMacBindStatusName           DisplayString,
    es2226IpMacBindStatusMac            DisplayString,
    es2226IpMacBindStatusIp             IpAddress,
    es2226IpMacBindStatusPort       DisplayString,
    es2226IpMacBindStatusBindingMethod      INTEGER,
    es2226IpMacBindStatusType       INTEGER,
    es2226IpMacBindStatusRowStatus    INTEGER
}

es2226IpMacBindStatusIndex  OBJECT-TYPE
    SYNTAX      INTEGER(1..2147483647)
    MAX-ACCESS      not-accessible
    STATUS      current
    DESCRIPTION
        "The index of the IP-MAC Binding entry."
    ::= { es2226IpMacBindStatusEntry 1 }

es2226IpMacBindStatusName   OBJECT-TYPE
    SYNTAX      DisplayString
    MAX-ACCESS      read-write
    STATUS      current
    DESCRIPTION
        "Get the name of this IP-MAC binding entry."
    ::= { es2226IpMacBindStatusEntry 2 }

es2226IpMacBindStatusMac    OBJECT-TYPE
    SYNTAX      DisplayString
    MAX-ACCESS      read-write
    STATUS      current
    DESCRIPTION
        "Get the MAC address of this IP-MAC binding entry."
    ::= { es2226IpMacBindStatusEntry 3 }

es2226IpMacBindStatusIp     OBJECT-TYPE
    SYNTAX      IpAddress
    MAX-ACCESS      read-write
    STATUS      current
    DESCRIPTION
        "Get the IP address of this IP-MAC binding entry."
    ::= { es2226IpMacBindStatusEntry 4 }

es2226IpMacBindStatusPort   OBJECT-TYPE
    SYNTAX      DisplayString
    MAX-ACCESS      read-write
    STATUS      current
    DESCRIPTION
        "Get the binding port of this IP-MAC binding entry."
    ::= { es2226IpMacBindStatusEntry 5 }

es2226IpMacBindStatusBindingMethod   OBJECT-TYPE
    SYNTAX      INTEGER(0|1)
    MAX-ACCESS      read-write
    STATUS      current
    DESCRIPTION
        "Get the binding method of this IP-MAC binding entry.
         0 : IP-MAC,
         1 : IP,
         2 : MAC"
    ::= { es2226IpMacBindStatusEntry 6 }

es2226IpMacBindStatusType   OBJECT-TYPE
    SYNTAX      INTEGER(0|1)
    MAX-ACCESS      read-only
    STATUS      current
    DESCRIPTION
        "Get the status of this IP-MAC binding entry.
         0: Static
         1: Dynamic"
    ::= { es2226IpMacBindStatusEntry 7 }

es2226IpMacBindStatusRowStatus  OBJECT-TYPE
    SYNTAX      INTEGER(1..3)
    MAX-ACCESS  read-write
    STATUS      current
    DESCRIPTION
        "1:active, 2:notInService, 3:delete."
    ::= { es2226IpMacBindStatusEntry 8 }

es2226MacTableInfo          	OBJECT IDENTIFIER ::= { es2226Produces 12 }

es2226MacTableMaintenance       OBJECT IDENTIFIER ::= { es2226MacTableInfo 1 }

es2226MacTableAgingTime  OBJECT-TYPE
    SYNTAX      INTEGER(0|10..1000000)
    MAX-ACCESS  read-write
    STATUS      current
    DESCRIPTION
        "Set the Mac Table Aging Time (10~1000000 Secs).
         0 : Disable.
        "
    ::= { es2226MacTableMaintenance 1 }

es2226MacTableFlush  OBJECT-TYPE
    SYNTAX      INTEGER(0|1)
    MAX-ACCESS  read-write
    STATUS      current
    DESCRIPTION
        "1 : Flush Mac Table."
    ::= { es2226MacTableMaintenance 2 }

es2226MacTableLearnPortLimitTable  OBJECT-TYPE
    SYNTAX      SEQUENCE OF ES2226MacTableLearnPortLimitEntry
    MAX-ACCESS  not-accessible
    STATUS      current
    DESCRIPTION
        " "
    ::= { es2226MacTableMaintenance 3 }

es2226MacTableLearnPortLimitEntry  OBJECT-TYPE
    SYNTAX      ES2226MacTableLearnPortLimitEntry
    MAX-ACCESS  not-accessible
    STATUS      current
    DESCRIPTION
        "Entry(s) for Mac Table Port Learning Limit."
    INDEX {es2226MacTableLearnPortLimitIndex}
    ::= { es2226MacTableLearnPortLimitTable 1 }

ES2226MacTableLearnPortLimitEntry ::=
SEQUENCE {
    es2226MacTableLearnPortLimitIndex   INTEGER,
    es2226MacTableLearnPortLimit       	INTEGER
}

es2226MacTableLearnPortLimitIndex  OBJECT-TYPE
    SYNTAX      INTEGER(1..26)
    MAX-ACCESS      read-only
    STATUS      current
    DESCRIPTION
        "The index of the Mac Table Learning Limit entry."
    ::= { es2226MacTableLearnPortLimitEntry 1 }

es2226MacTableLearnPortLimit  OBJECT-TYPE
    SYNTAX      INTEGER(0..8191)
    MAX-ACCESS  read-write
    STATUS      current
    DESCRIPTION
        "Port Learning Limit (0~8191)."
    ::= { es2226MacTableLearnPortLimitEntry 2 }

es2226MacTableStaticMac      OBJECT IDENTIFIER ::= { es2226MacTableInfo 2 }

es2226MacTableStaticMacCreatStatus OBJECT-TYPE
    SYNTAX         INTEGER(0|1)
    MAX-ACCESS     read-write
    STATUS         current
    DESCRIPTION
        "Create a new high-acl
         0 : None,
         1 : Create a static mac temp entry
        "
    ::= { es2226MacTableStaticMac 1 }

es2226MacTableStaticMacNumber  OBJECT-TYPE
    SYNTAX      INTEGER(0..1024)
    MAX-ACCESS  read-only
    STATUS      current
    DESCRIPTION
        "Static Mac Total Nnumber(0~1024)."
    ::= { es2226MacTableStaticMac 2 }

es2226MacTableStaticMacTable  OBJECT-TYPE
    SYNTAX      SEQUENCE OF ES2226MacTableStaticMacEntry
    MAX-ACCESS  not-accessible
    STATUS      current
    DESCRIPTION
        " "
    ::= { es2226MacTableStaticMac 3 }

es2226MacTableStaticMacEntry  OBJECT-TYPE
    SYNTAX      ES2226MacTableStaticMacEntry
    MAX-ACCESS  not-accessible
    STATUS      current
    DESCRIPTION
        "Entry(s) for Static Mac Table."
    INDEX {es2226MacTableStaticMacIndex}
    ::= { es2226MacTableStaticMacTable 1 }

ES2226MacTableStaticMacEntry ::=
SEQUENCE {
    es2226MacTableStaticMacIndex	INTEGER,
    es2226MacTableStaticMacAddress   	DisplayString,
    es2226MacTableStaticMacVid       	INTEGER,
    es2226MacTableStaticMacRule       	INTEGER,
    es2226MacTableStaticMacPort       	INTEGER,
    es2226MacTableStaticMacRowStatus    INTEGER
}

es2226MacTableStaticMacIndex  OBJECT-TYPE
    SYNTAX      INTEGER(1..1024)
    MAX-ACCESS  not-accessible
    STATUS      current
    DESCRIPTION
        "The index of the static mac table entry."
    ::= { es2226MacTableStaticMacEntry 1 }

es2226MacTableStaticMacAddress  OBJECT-TYPE
    SYNTAX      DisplayString
    MAX-ACCESS  read-write
    STATUS      current
    DESCRIPTION
        "The mac address of the static mac table entry."
    ::= { es2226MacTableStaticMacEntry 2 }

es2226MacTableStaticMacVid  OBJECT-TYPE
    SYNTAX      INTEGER(1..4094)
    MAX-ACCESS  read-write
    STATUS      current
    DESCRIPTION
        "The vlan id of the static mac table entry."
    ::= { es2226MacTableStaticMacEntry 3 }

es2226MacTableStaticMacRule  OBJECT-TYPE
    SYNTAX      INTEGER(0..2)
    MAX-ACCESS  read-write
    STATUS      current
    DESCRIPTION
        "The forwarding rule of the static mac table entry.
         0 : static,
         1 : Static with Destination Drop,
         2 : Static with Source Drop
        "
    ::= { es2226MacTableStaticMacEntry 4 }

es2226MacTableStaticMacPort  OBJECT-TYPE
    SYNTAX      INTEGER(1..26)
    MAX-ACCESS  read-write
    STATUS      current
    DESCRIPTION
        "The port of the static mac table entry."
    ::= { es2226MacTableStaticMacEntry 5 }

es2226MacTableStaticMacRowStatus  OBJECT-TYPE
    SYNTAX      INTEGER(1..3)
    MAX-ACCESS  read-write
    STATUS      current
    DESCRIPTION
        "1:active, 2:notInService, 3:delete."
    ::= { es2226MacTableStaticMacEntry 6 }

es2226MacTableMacAlias       OBJECT IDENTIFIER ::= { es2226MacTableInfo 3 }

es2226MacTableMacAliasCreatStatus  OBJECT-TYPE
    SYNTAX      INTEGER(0|1)
    MAX-ACCESS  read-write
    STATUS      current
    DESCRIPTION
        "0:not add, 1:add."
    ::= { es2226MacTableMacAlias 1 }

es2226MacTableMacAliasNumber  OBJECT-TYPE
    SYNTAX      INTEGER(0..1024)
    MAX-ACCESS  read-write
    STATUS      current
    DESCRIPTION
        "Mac Alias Total Nnumber(0~1024)."
    ::= { es2226MacTableMacAlias 2 }

es2226MacTableMacAliasTable  OBJECT-TYPE
    SYNTAX      SEQUENCE OF ES2226MacTableMacAliasEntry
    MAX-ACCESS  not-accessible
    STATUS      current
    DESCRIPTION
        " "
    ::= { es2226MacTableMacAlias 3 }

es2226MacTableMacAliasEntry OBJECT-TYPE
    SYNTAX      ES2226MacTableMacAliasEntry
    MAX-ACCESS  not-accessible
    STATUS      current
    DESCRIPTION
        "Entry(s) for Mac Alias."
    INDEX {es2226MacTableMacAliasIndex}
    ::= { es2226MacTableMacAliasTable 1 }

ES2226MacTableMacAliasEntry ::=
SEQUENCE {
    es2226MacTableMacAliasIndex		INTEGER,
    es2226MacTableMacAliasAddress   	MacAddress,
    es2226MacTableMacAliasAlias       	DisplayString,
    es2226MacTableMacAliasRowStatus     INTEGER
}

es2226MacTableMacAliasIndex  OBJECT-TYPE
    SYNTAX      INTEGER(1..1024)
    MAX-ACCESS  not-accessible
    STATUS      current
    DESCRIPTION
        "The index of the static mac alias entry."
    ::= { es2226MacTableMacAliasEntry 1 }

es2226MacTableMacAliasAddress  OBJECT-TYPE
    SYNTAX      DisplayString
    MAX-ACCESS  read-write
    STATUS      current
    DESCRIPTION
        "The mac address of the mac alias table entry."
    ::= { es2226MacTableMacAliasEntry 2 }

es2226MacTableMacAliasAlias  OBJECT-TYPE
    SYNTAX      DisplayString
    MAX-ACCESS  read-write
    STATUS      current
    DESCRIPTION
        "The alias of the mac alias table entry."
    ::= { es2226MacTableMacAliasEntry 3 }

es2226MacTableMacAliasRowStatus  OBJECT-TYPE
    SYNTAX      INTEGER(1..3)
    MAX-ACCESS  read-write
    STATUS      current
    DESCRIPTION
        "1:active, 2:notInService, 3:delete."
    ::= { es2226MacTableMacAliasEntry 4 }

es2226Security          	OBJECT IDENTIFIER ::= { es2226Produces 13 }

es2226Mirror      OBJECT IDENTIFIER ::= { es2226Security 1 }

es2226MirrorMode  OBJECT-TYPE
    SYNTAX      INTEGER(0|1)
    MAX-ACCESS  read-write
    STATUS      current
    DESCRIPTION
        "Set the Mirror Enable/Disable Mode.
         0 : Mirror Disable,
         1 : Mirror Enable.
        "
    ::= { es2226Mirror 1 }

es2226MonitoringPort  OBJECT-TYPE
    SYNTAX      INTEGER(0..26)
    MAX-ACCESS  read-write
    STATUS      current
    DESCRIPTION
        "Set the Mirror Monitoring Port.(1~26)"
    ::= { es2226Mirror 2 }

es2226MonitoredIngressPort  OBJECT-TYPE
    SYNTAX      DisplayString
    MAX-ACCESS  read-write
    STATUS      current
    DESCRIPTION
        "Set monitored ingress port; range syntax: 1,5-7, available from 0 to 26.
         0 : Ingress Disable,
         1~26 : Ingress Enable.
        "
    ::= { es2226Mirror 3 }

es2226MonitoredEgressPort  OBJECT-TYPE
    SYNTAX      DisplayString
    MAX-ACCESS  read-write
    STATUS      current
    DESCRIPTION
        "Set monitored egress port; range syntax: 1,5-7, available from 0 to 26.
         0 : Egress Disable,
         1~26 : Egress Enable.
        "
    ::= { es2226Mirror 4 }

es2226IsolatedGroup      OBJECT IDENTIFIER ::= { es2226Security 2 }

es2226IsolatedPortGroup  OBJECT-TYPE
    SYNTAX      DisplayString
    MAX-ACCESS  read-write
    STATUS      current
    DESCRIPTION
        "Set the Isolated Group; range syntax: 1,5-7, available from 0 to 26.
         0 : Isolated Group Disable,
         1~26 : Isolated Group Enable
        "
    ::= { es2226IsolatedGroup 1 }

es2226ArpProtect      OBJECT IDENTIFIER ::= { es2226Security 3 }

es2226ArpProtectPackerBurst  OBJECT-TYPE
    SYNTAX      INTEGER(0..200)
    MAX-ACCESS  read-write
    STATUS      current
    DESCRIPTION
        "Set the packet-burst.
         range : 1~200 packets
           0   : No limit"
    ::= { es2226ArpProtect 1 }

es2226ArpProtectRatePerSec  OBJECT-TYPE
    SYNTAX      INTEGER(0|64..25600)
    MAX-ACCESS  read-write
    STATUS      current
    DESCRIPTION
        "Set the rate-per-second.
         range : 64~25600 Bytes
           0   : No limit"
    ::= { es2226ArpProtect 2 }

es2226VirtualStack        OBJECT IDENTIFIER ::= { es2226Produces 14 }

es2226VirtualStackState   OBJECT-TYPE
    SYNTAX      INTEGER(0|1)
    MAX-ACCESS  read-write
    STATUS      current
    DESCRIPTION
        "Set the Virtual Stack State.
         0 : disable,
         1 : enable
        "
    ::= { es2226VirtualStack 1 }

es2226VirtualStackRole   OBJECT-TYPE
    SYNTAX      INTEGER(0|1)
    MAX-ACCESS  read-write
    STATUS      current
    DESCRIPTION
        "Set the Virtual Stack Role.
         0 : slave,
         1 : master
        "
    ::= { es2226VirtualStack 2 }

es2226VirtualStackGroupID  OBJECT-TYPE
    SYNTAX      DisplayString
    MAX-ACCESS  read-write
    STATUS      current
    DESCRIPTION
        "Set the Virtual Stack Group ID."
    ::= { es2226VirtualStack 3 }

es2226ManagementSecurity        OBJECT IDENTIFIER ::= { es2226Produces 15 }

es2226ManagementSecurityNumber  OBJECT-TYPE
    SYNTAX      INTEGER(0..64)
    MAX-ACCESS  read-only
    STATUS      current
    DESCRIPTION
        "The Number of Management Security Entry."
    ::= { es2226ManagementSecurity 1 }

es2226ManagementSecurityEntryCreate  OBJECT-TYPE
    SYNTAX      INTEGER(0|1)
    MAX-ACCESS  read-write
    STATUS      current
    DESCRIPTION
        "Create management security entry."
    ::= { es2226ManagementSecurity 2 }

es2226ManagementSecurityTable  OBJECT-TYPE
    SYNTAX      SEQUENCE OF ES2226ManagementSecurityEntry
    MAX-ACCESS  not-accessible
    STATUS      current
    DESCRIPTION
        " "
    ::= { es2226ManagementSecurity 3 }

es2226ManagementSecurityEntry OBJECT-TYPE
    SYNTAX      ES2226ManagementSecurityEntry
    MAX-ACCESS  not-accessible
    STATUS      current
    DESCRIPTION
        "Entry(s) for Management Security."
    INDEX {es2226ManagementSecurityIndex}
    ::= { es2226ManagementSecurityTable 1 }

ES2226ManagementSecurityEntry ::=
SEQUENCE {
    es2226ManagementSecurityIndex		INTEGER,
    es2226ManagementSecurityName   		DisplayString,
    es2226ManagementSecurityVid       		INTEGER,
    es2226ManagementSecurityIpRange   		DisplayString,
    es2226ManagementSecurityIncomigPort   	DisplayString,
    es2226ManagementSecurityAccessType		DisplayString,
    es2226ManagementSecurityAction		INTEGER,
    es2226ManagementSecurityRowStatus		INTEGER
}

es2226ManagementSecurityIndex  OBJECT-TYPE
    SYNTAX      INTEGER(1..64)
    MAX-ACCESS  not-accessible
    STATUS      current
    DESCRIPTION
        "The index of management security entry."
    ::= { es2226ManagementSecurityEntry 1 }

es2226ManagementSecurityName  OBJECT-TYPE
    SYNTAX      DisplayString
    MAX-ACCESS  read-write
    STATUS      current
    DESCRIPTION
        "The name of management security entry."
    ::= { es2226ManagementSecurityEntry 2 }

es2226ManagementSecurityVid  OBJECT-TYPE
    SYNTAX      INTEGER(0..4094)
    MAX-ACCESS  read-write
    STATUS      current
    DESCRIPTION
        "The vid of management security entry.
         vid 0 : Any.
        "
    ::= { es2226ManagementSecurityEntry 3 }

es2226ManagementSecurityIpRange  OBJECT-TYPE
    SYNTAX      DisplayString
    MAX-ACCESS  read-write
    STATUS      current
    DESCRIPTION
        "The ip range of management security entry(StartIP-EndIP).
         ex : 192.168.1.1-192.168.1.255,
         0 : any.
        "
    ::= { es2226ManagementSecurityEntry 4 }

es2226ManagementSecurityIncomigPort  OBJECT-TYPE
    SYNTAX      DisplayString
    MAX-ACCESS  read-write
    STATUS      current
    DESCRIPTION
        "The incoming Port of management security entry.
         range syntax: 1,5-7, available from 0 to 26,
         0 : Any.
        "
    ::= { es2226ManagementSecurityEntry 5 }

es2226ManagementSecurityAccessType  OBJECT-TYPE
    SYNTAX      DisplayString
    MAX-ACCESS  read-write
    STATUS      current
    DESCRIPTION
        "The access type of management security entry.
         range syntax: 1,3 or 1-3, available from 0 to 3.
         0 : Any,
         1 : http,
         2 : telnet,
         3 : snmp
        "
    ::= { es2226ManagementSecurityEntry 6 }

es2226ManagementSecurityAction  OBJECT-TYPE
    SYNTAX      INTEGER(0|1)
    MAX-ACCESS  read-write
    STATUS      current
    DESCRIPTION
        "The action of management security entry.
         0 : deny,
         1 : accept.
        "
    ::= { es2226ManagementSecurityEntry 7 }

es2226ManagementSecurityRowStatus  OBJECT-TYPE
    SYNTAX      INTEGER(1..3)
    MAX-ACCESS  read-write
    STATUS      current
    DESCRIPTION
        "The row status of management security entry.
   	1 - active.
   	2 - notInService.
   	3 - delete."
    ::= { es2226ManagementSecurityEntry 8 }

es2226QoS       OBJECT IDENTIFIER ::= { es2226Produces 16 }

es2226QoSGlobalConfig      OBJECT IDENTIFIER ::= { es2226QoS 1 }

es2226QoSMode OBJECT-TYPE
    SYNTAX      INTEGER(0|1)
    MAX-ACCESS  read-write
    STATUS      current
    DESCRIPTION
        "Set the Qos Mode Enable/Disable.
         0 : Disable,
         1 : Enable.
        "
    ::= { es2226QoSGlobalConfig 1 }

es2226QoS1PEnable OBJECT-TYPE
    SYNTAX      INTEGER(0|1)
    MAX-ACCESS  read-write
    STATUS      current
    DESCRIPTION
        "Set the Qos 802.1P Enable/Disable.
         0 : Disable,
         1 : Enable.
        "
    ::= { es2226QoSGlobalConfig 2 }

es2226QoSDSCPEnable OBJECT-TYPE
    SYNTAX      INTEGER(0|1)
    MAX-ACCESS  read-write
    STATUS      current
    DESCRIPTION
        "Set the Qos DSCP Enable/Disable.
         0 : Disable,
         1 : Enable.
        "
    ::= { es2226QoSGlobalConfig 3 }

es2226QoSSchedulingMethod OBJECT-TYPE
    SYNTAX      INTEGER(0..3)
    MAX-ACCESS  read-write
    STATUS      current
    DESCRIPTION
        "Set the Qos Scheduling Method(0~3).
	 0 : 4 WRR
	 1 : 1 Strict, 3 WRR
	 2 : 2 Strict, 2 WRR
	 3 : 4 Strict
        "
    ::= { es2226QoSGlobalConfig 4 }

es2226QoSWeightQ0 OBJECT-TYPE
    SYNTAX      INTEGER(1..55)
    MAX-ACCESS  read-write
    STATUS      current
    DESCRIPTION
        "Set the Qos Queue 0 Weight(1~55)."
    ::= { es2226QoSGlobalConfig 5 }

es2226QoSWeightQ1 OBJECT-TYPE
    SYNTAX      INTEGER(1..55)
    MAX-ACCESS  read-write
    STATUS      current
    DESCRIPTION
        "Set the Qos Queue 1 Weight(1~55)."
    ::= { es2226QoSGlobalConfig 6 }

es2226QoSWeightQ2 OBJECT-TYPE
    SYNTAX      INTEGER(1..55)
    MAX-ACCESS  read-write
    STATUS      current
    DESCRIPTION
        "Set the Qos Queue 2 Weight(1~55)."
    ::= { es2226QoSGlobalConfig 7 }

es2226QoSWeightQ3 OBJECT-TYPE
    SYNTAX      INTEGER(1..55)
    MAX-ACCESS  read-write
    STATUS      current
    DESCRIPTION
        "Set the Qos Queue 3 Weight(1~55)."
    ::= { es2226QoSGlobalConfig 8 }

es2226QoS1PPriority      OBJECT IDENTIFIER ::= { es2226QoS 2 }

es2226QoS1PPriorityTable  OBJECT-TYPE
    SYNTAX      SEQUENCE OF ES2226QoS1PPriorityEntry
    MAX-ACCESS  not-accessible
    STATUS      current
    DESCRIPTION
        " "
    ::= { es2226QoS1PPriority 1 }

es2226QoS1PPriorityEntry OBJECT-TYPE
    SYNTAX      ES2226QoS1PPriorityEntry
    MAX-ACCESS  not-accessible
    STATUS      current
    DESCRIPTION
        "Entry(s) for QoS 802.1P Priority."
    INDEX {es2226QoS1PPriorityIndex}
    ::= { es2226QoS1PPriorityTable 1 }

ES2226QoS1PPriorityEntry ::=
SEQUENCE {
    es2226QoS1PPriorityIndex		INTEGER,
    es2226QoS1PPriorityValue		INTEGER,
    es2226QoS1PPriorityQueue   		INTEGER
}

es2226QoS1PPriorityIndex  OBJECT-TYPE
    SYNTAX      INTEGER(1..8)
    MAX-ACCESS  not-accessible
    STATUS      current
    DESCRIPTION
        "The Priority index of QoS 802.1P Priority entry."
    ::= { es2226QoS1PPriorityEntry 1 }

es2226QoS1PPriorityValue  OBJECT-TYPE
    SYNTAX      INTEGER(0..7)
    MAX-ACCESS  read-only
    STATUS      current
    DESCRIPTION
        "The Priority value of QoS 802.1P Priority entry."
    ::= { es2226QoS1PPriorityEntry 2 }

es2226QoS1PPriorityQueue  OBJECT-TYPE
    SYNTAX      INTEGER(0..3)
    MAX-ACCESS  read-write
    STATUS      current
    DESCRIPTION
        "The Queue(0~3) of QoS 802.1P Priority."
    ::= { es2226QoS1PPriorityEntry 3 }

es2226QoSDSCPPriority      OBJECT IDENTIFIER ::= { es2226QoS 3 }

es2226QoSDSCPPriorityTable  OBJECT-TYPE
    SYNTAX      SEQUENCE OF ES2226QoSDSCPPriorityEntry
    MAX-ACCESS  not-accessible
    STATUS      current
    DESCRIPTION
        " "
    ::= { es2226QoSDSCPPriority 1 }

es2226QoSDSCPPriorityEntry OBJECT-TYPE
    SYNTAX      ES2226QoSDSCPPriorityEntry
    MAX-ACCESS  not-accessible
    STATUS      current
    DESCRIPTION
        "Entry(s) for QoS DSCP Priority."
    INDEX {es2226QoSDSCPPriorityIndex}
    ::= { es2226QoSDSCPPriorityTable 1 }

ES2226QoSDSCPPriorityEntry ::=
SEQUENCE {
    es2226QoSDSCPPriorityIndex		INTEGER,
    es2226QoSDSCPPriorityValue		INTEGER,
    es2226QoSDSCPPriorityQueue   	INTEGER
}

es2226QoSDSCPPriorityIndex  OBJECT-TYPE
    SYNTAX      INTEGER(1..64)
    MAX-ACCESS  not-accessible
    STATUS      current
    DESCRIPTION
        "The Priority index of QoS DSCP Priority entry."
    ::= { es2226QoSDSCPPriorityEntry 1 }

es2226QoSDSCPPriorityValue  OBJECT-TYPE
    SYNTAX      INTEGER(0..3)
    MAX-ACCESS  read-only
    STATUS      current
    DESCRIPTION
        "The Priority value of QoS DSCP Priority entry."
    ::= { es2226QoSDSCPPriorityEntry 2 }

es2226QoSDSCPPriorityQueue  OBJECT-TYPE
    SYNTAX      INTEGER(0..3)
    MAX-ACCESS  read-write
    STATUS      current
    DESCRIPTION
        "The Queue(0~3) of QoS DSCP Priority."
    ::= { es2226QoSDSCPPriorityEntry 3 }

es2226Vlan      OBJECT IDENTIFIER ::= { es2226Produces 17 }

es2226VlanModeConfig      OBJECT IDENTIFIER ::= { es2226Vlan 1 }

es2226VlanMode  OBJECT-TYPE
    SYNTAX      INTEGER(0..2)
    MAX-ACCESS  read-write
    STATUS      current
    DESCRIPTION
        "0:Tag-based, 1:Port-based, 2:Metro mode"
    ::= { es2226VlanModeConfig 1 }

es2226SymmetricVlan  OBJECT-TYPE
    SYNTAX      INTEGER(0|1)
    MAX-ACCESS  read-write
    STATUS      current
    DESCRIPTION
        "0:disable, 1:enable"
    ::= { es2226VlanModeConfig 2 }

es2226VlanSVL  OBJECT-TYPE
    SYNTAX      INTEGER(0|1)
    MAX-ACCESS  read-write
    STATUS      current
    DESCRIPTION
        "0:disable, 1:enable"
    ::= { es2226VlanModeConfig 3 }

es2226DoubleTag  OBJECT-TYPE
    SYNTAX      INTEGER(0..2)
    MAX-ACCESS  read-write
    STATUS      current
    DESCRIPTION
        "0 : disable,
         1 : enable SP-tag 0x88A8,
         2 : enable SP-tag 0x8100
        "
    ::= { es2226VlanModeConfig 4 }

es2226SpPortMember  OBJECT-TYPE
    SYNTAX      DisplayString
    MAX-ACCESS  read-write
    STATUS      current
    DESCRIPTION
        "The member of Service Provider Port.
         Port range syntax: 1,5-7, available from 1 to 26
        "
    ::= { es2226VlanModeConfig 5 }

es2226UpLinkPort  OBJECT-TYPE
    SYNTAX      INTEGER(0..2)
    MAX-ACCESS  read-write
    STATUS      current
    DESCRIPTION
        "0:Port 25, 1:Port 26, 2:Port 25 & 26"
    ::= { es2226VlanModeConfig 6 }

es2226VlanPvid      OBJECT IDENTIFIER ::= { es2226Vlan 2 }

es2226VlanPvidTable  OBJECT-TYPE
    SYNTAX      SEQUENCE OF ES2226VlanPvidEntry
    MAX-ACCESS  not-accessible
    STATUS      current
    DESCRIPTION
        " "
    ::= { es2226VlanPvid 1 }

es2226VlanPvidEntry OBJECT-TYPE
    SYNTAX      ES2226VlanPvidEntry
    MAX-ACCESS  not-accessible
    STATUS      current
    DESCRIPTION
        "Entry(s) for Vlan Pvid."
    INDEX {es2226VlanPvidPort}
    ::= { es2226VlanPvidTable 1 }

ES2226VlanPvidEntry ::=
SEQUENCE {
    es2226VlanPvidPort				INTEGER,
    es2226VlanPvidValue   			INTEGER,
    es2226VlanPvidDefaultPriority      		INTEGER,
    es2226VlanPvidDropUntag   			INTEGER
}

es2226VlanPvidPort  OBJECT-TYPE
    SYNTAX      INTEGER(1..26)
    MAX-ACCESS  not-accessible
    STATUS      current
    DESCRIPTION
        "The port number of pvid entry."
    ::= { es2226VlanPvidEntry 1 }

es2226VlanPvidValue  OBJECT-TYPE
    SYNTAX      INTEGER(1..4094)
    MAX-ACCESS  read-write
    STATUS      current
    DESCRIPTION
        "The pvid value of port."
    ::= { es2226VlanPvidEntry 2 }

es2226VlanPvidDefaultPriority  OBJECT-TYPE
    SYNTAX      INTEGER(0..7)
    MAX-ACCESS  read-write
    STATUS      current
    DESCRIPTION
        "The default priority of port ."
    ::= { es2226VlanPvidEntry 3 }

es2226VlanPvidDropUntag  OBJECT-TYPE
    SYNTAX      INTEGER(0|1)
    MAX-ACCESS  read-write
    STATUS      current
    DESCRIPTION
        "The drop untag of port ."
    ::= { es2226VlanPvidEntry 4 }

es2226PortBasedVlanGroup      OBJECT IDENTIFIER ::= { es2226Vlan 3 }

es2226PortBasedVlanNumbers  OBJECT-TYPE
    SYNTAX      INTEGER(1..26)
    MAX-ACCESS  read-only
    STATUS      current
    DESCRIPTION
        "Total numbers for tag-based vlan."
    ::= { es2226PortBasedVlanGroup 1 }

es2226PortBasedCreateStatus  OBJECT-TYPE
    SYNTAX      INTEGER(0|1)
    MAX-ACCESS  read-write
    STATUS      current
    DESCRIPTION
        "Creat a temp vlan in port-based vlan table.
         0 : none,
         1 : creat a new port-based vlan.
        "
    ::= { es2226PortBasedVlanGroup 2 }

es2226PortBasedVlanTable  OBJECT-TYPE
    SYNTAX      SEQUENCE OF ES2226PortBasedVlanEntry
    MAX-ACCESS  not-accessible
    STATUS      current
    DESCRIPTION
        " "
    ::= { es2226PortBasedVlanGroup 3 }

es2226PortBasedVlanEntry OBJECT-TYPE
    SYNTAX      ES2226PortBasedVlanEntry
    MAX-ACCESS  not-accessible
    STATUS      current
    DESCRIPTION
        "Entry(s) for port-based vlan table."
    INDEX {es2226PortBasedVlanIndex}
    ::= { es2226PortBasedVlanTable 1 }

ES2226PortBasedVlanEntry ::=
SEQUENCE {
    es2226PortBasedVlanIndex				INTEGER,
    es2226PortBasedVlanName   				DisplayString,
    es2226PortBasedVlanMember  				DisplayString,
    es2226PortBasedVlanRowStatus			INTEGER
}

es2226PortBasedVlanIndex  OBJECT-TYPE
    SYNTAX      INTEGER(1..26)
    MAX-ACCESS  not-accessible
    STATUS      current
    DESCRIPTION
        "The index of vlan."
    ::= { es2226PortBasedVlanEntry 1 }

es2226PortBasedVlanName  OBJECT-TYPE
    SYNTAX      DisplayString
    MAX-ACCESS  read-write
    STATUS      current
    DESCRIPTION
        "The name of vlan."
    ::= { es2226PortBasedVlanEntry 2 }

es2226PortBasedVlanMember  OBJECT-TYPE
    SYNTAX      DisplayString
    MAX-ACCESS  read-write
    STATUS      current
    DESCRIPTION
        "The member of vlan."
    ::= { es2226PortBasedVlanEntry 3 }

es2226PortBasedVlanRowStatus  OBJECT-TYPE
    SYNTAX      INTEGER(1..3)
    MAX-ACCESS  read-write
    STATUS      current
    DESCRIPTION
        "The row status of vlan.
         1 : active,
         2 : not-inService,
         3 : delete
        "
    ::= { es2226PortBasedVlanEntry 4 }

es2226ManagementVlan      OBJECT IDENTIFIER ::= { es2226Vlan 4 }

es2226ManagementVlanState  OBJECT-TYPE
    SYNTAX      INTEGER(0|1)
    MAX-ACCESS  read-write
    STATUS      current
    DESCRIPTION
        "The stat of management vlan.
         0 : Disable,
         1 : Enable.
        "
    ::= { es2226ManagementVlan 1 }

es2226ManagementVlanVid  OBJECT-TYPE
    SYNTAX      INTEGER(1..4094)
    MAX-ACCESS  read-write
    STATUS      current
    DESCRIPTION
        "The vid value of management vlan."
    ::= { es2226ManagementVlan 2 }

es2226DhcpSnooping        OBJECT IDENTIFIER ::= { es2226Produces 18 }

es2226DhcpSnoopingConf      OBJECT IDENTIFIER ::= { es2226DhcpSnooping 1 }

es2226DhcpSnoopingState OBJECT-TYPE
    SYNTAX         INTEGER(0|1)
    MAX-ACCESS     read-write
    STATUS         current
    DESCRIPTION
        "Set DHCP Snooping State.
         0 : Disable,
         1 : Enable.
         When DHCP Relay is already running. Please disable DHCP Relay first, and then enable DHCP Snooping again.
        "
    ::= { es2226DhcpSnoopingConf 1 }

es2226DhcpSnoopingPortCountSetupTable  OBJECT-TYPE
    SYNTAX      SEQUENCE OF ES2226DhcpSnoopingPortCountSetupEntry
    MAX-ACCESS  not-accessible
    STATUS      current
    DESCRIPTION
        " "
    ::= { es2226DhcpSnoopingConf 2 }

es2226DhcpSnoopingPortCountSetupEntry OBJECT-TYPE
    SYNTAX      ES2226DhcpSnoopingPortCountSetupEntry
    MAX-ACCESS  not-accessible
    STATUS      current
    DESCRIPTION
        "Entry(s) for DHCP snooping port count table."
    INDEX {es2226DhcpSnoopingPortCountSetupPortIndex}
    ::= { es2226DhcpSnoopingPortCountSetupTable 1 }

ES2226DhcpSnoopingPortCountSetupEntry ::=
SEQUENCE {
    es2226DhcpSnoopingPortCountSetupPortIndex		INTEGER,
    es2226DhcpSnoopingPortCountSetupCount		INTEGER
}

es2226DhcpSnoopingPortCountSetupPortIndex  OBJECT-TYPE
    SYNTAX      INTEGER(1..26)
    MAX-ACCESS  not-accessible
    STATUS      current
    DESCRIPTION
        "The port index of DHCP snooping port count table."
    ::= { es2226DhcpSnoopingPortCountSetupEntry 1 }

es2226DhcpSnoopingPortCountSetupCount OBJECT-TYPE
    SYNTAX         INTEGER(0..512)
    MAX-ACCESS     read-write
    STATUS         current
    DESCRIPTION
        "Set client-count. Limit range from 0 to 512. 0 for disable."
    ::= { es2226DhcpSnoopingPortCountSetupEntry 2 }

es2226DhcpSnoopingTrustGroupConf     OBJECT IDENTIFIER ::= { es2226DhcpSnooping 2 }

es2226DhcpSnoopingTrustGroupNumbers OBJECT-TYPE
    SYNTAX         INTEGER(0..128)
    MAX-ACCESS     read-only
    STATUS         current
    DESCRIPTION
        "Numbers of DHCP snooping trust group"
    ::= { es2226DhcpSnoopingTrustGroupConf 1 }

es2226DhcpSnoopingTrustGroupCreatStatus OBJECT-TYPE
    SYNTAX         INTEGER(1..4094)
    MAX-ACCESS     read-write
    STATUS         current
    DESCRIPTION
        "Creat a temp trust group in table.
         range : 1~4094"
    ::= { es2226DhcpSnoopingTrustGroupConf 2 }

es2226DhcpSnoopingTrustGroupTable  OBJECT-TYPE
    SYNTAX      SEQUENCE OF ES2226DhcpSnoopingTrustGroupEntry
    MAX-ACCESS  not-accessible
    STATUS      current
    DESCRIPTION
        " "
    ::= { es2226DhcpSnoopingTrustGroupConf 3 }

es2226DhcpSnoopingTrustGroupEntry OBJECT-TYPE
    SYNTAX      ES2226DhcpSnoopingTrustGroupEntry
    MAX-ACCESS  not-accessible
    STATUS      current
    DESCRIPTION
        "Entry(s) for DHCP snooping trust group table."
    INDEX {es2226DhcpSnoopingTrustGroupIndex}
    ::= { es2226DhcpSnoopingTrustGroupTable 1 }

ES2226DhcpSnoopingTrustGroupEntry ::=
SEQUENCE {
    es2226DhcpSnoopingTrustGroupIndex			INTEGER,
    es2226DhcpSnoopingTrustGroupTrustVid		INTEGER,
    es2226DhcpSnoopingTrustGroupOption82		INTEGER,
    es2226DhcpSnoopingTrustGroupAction			INTEGER,
    es2226DhcpSnoopingTrustGroupServerPort		DisplayString,
    es2226DhcpSnoopingTrustGroupServerVid		INTEGER,
    es2226DhcpSnoopingTrustGroupServerIp		IpAddress,
    es2226DhcpSnoopingTrustGroupRowStatus		INTEGER
}

es2226DhcpSnoopingTrustGroupIndex  OBJECT-TYPE
    SYNTAX      INTEGER(1..4095)
    MAX-ACCESS  not-accessible
    STATUS      current
    DESCRIPTION
        "The index of DHCP snooping trust group table."
    ::= { es2226DhcpSnoopingTrustGroupEntry 1 }

es2226DhcpSnoopingTrustGroupTrustVid OBJECT-TYPE
    SYNTAX         INTEGER(1..4094)
    MAX-ACCESS     read-write
    STATUS         current
    DESCRIPTION
        "Trust Vid in turst group.
         range : 1~4094."
    ::= { es2226DhcpSnoopingTrustGroupEntry 2 }

es2226DhcpSnoopingTrustGroupOption82 OBJECT-TYPE
    SYNTAX         INTEGER(0|1)
    MAX-ACCESS     read-write
    STATUS         current
    DESCRIPTION
        "Option82 state in turst group.
         0 : Disable,
         1 : Enable."
    ::= { es2226DhcpSnoopingTrustGroupEntry 3 }

es2226DhcpSnoopingTrustGroupAction OBJECT-TYPE
    SYNTAX         INTEGER(0..2)
    MAX-ACCESS     read-write
    STATUS         current
    DESCRIPTION
        "Action in turst group.
         0 : Replace,
         1 : Keep,
         2 : Drop."
    ::= { es2226DhcpSnoopingTrustGroupEntry 4 }

es2226DhcpSnoopingTrustGroupServerPort OBJECT-TYPE
    SYNTAX         DisplayString
    MAX-ACCESS     read-write
    STATUS         current
    DESCRIPTION
        "Trust port in turst group.
         Trust port with range format, max port 2 ports"
    ::= { es2226DhcpSnoopingTrustGroupEntry 5 }

es2226DhcpSnoopingTrustGroupServerVid OBJECT-TYPE
    SYNTAX         INTEGER(1..4094)
    MAX-ACCESS     read-write
    STATUS         current
    DESCRIPTION
        "Server Vid in turst group.
         range : 1~4094."
    ::= { es2226DhcpSnoopingTrustGroupEntry 6 }

es2226DhcpSnoopingTrustGroupServerIp OBJECT-TYPE
    SYNTAX         IpAddress
    MAX-ACCESS     read-write
    STATUS         current
    DESCRIPTION
        "Server ip in turst group."
    ::= { es2226DhcpSnoopingTrustGroupEntry 7 }

es2226DhcpSnoopingTrustGroupRowStatus  OBJECT-TYPE
    SYNTAX      INTEGER(1..3)
    MAX-ACCESS  read-write
    STATUS      current
    DESCRIPTION
        "The row status of trust group.
         1 : active,
         2 : not-inService,
         3 : delete
        "
    ::= { es2226DhcpSnoopingTrustGroupEntry 8 }

es2226DhcpSnoopingDefaultGroupConf     OBJECT IDENTIFIER ::= { es2226DhcpSnooping 3 }

es2226DhcpSnoopingDefaultGroupServerPort OBJECT-TYPE
    SYNTAX         DisplayString
    MAX-ACCESS     read-write
    STATUS         current
    DESCRIPTION
        "Server port in default turst group.
         Server port with range format, max port 2 ports, 0 for disabled"
    ::= { es2226DhcpSnoopingDefaultGroupConf 1 }

es2226DhcpSnoopingDefaultGroupServerVid OBJECT-TYPE
    SYNTAX         INTEGER(1..4094)
    MAX-ACCESS     read-write
    STATUS         current
    DESCRIPTION
        "Server Vid in default turst group.
         range : 1~4094."
    ::= { es2226DhcpSnoopingDefaultGroupConf 2 }

es2226DhcpSnoopingDefaultGroupOption82 OBJECT-TYPE
    SYNTAX         INTEGER(0|1)
    MAX-ACCESS     read-write
    STATUS         current
    DESCRIPTION
        "Option82 state in default turst group.
         0 : Disable,
         1 : Enable."
    ::= { es2226DhcpSnoopingDefaultGroupConf 3 }

es2226DhcpSnoopingDefaultGroupAction OBJECT-TYPE
    SYNTAX         INTEGER(0..2)
    MAX-ACCESS     read-write
    STATUS         current
    DESCRIPTION
        "Action in turst group.
         0 : Replace,
         1 : Keep,
         2 : Drop."
    ::= { es2226DhcpSnoopingDefaultGroupConf 4 }

es2226DhcpSnoopingDefaultGroupServerIp OBJECT-TYPE
    SYNTAX         IpAddress
    MAX-ACCESS     read-write
    STATUS         current
    DESCRIPTION
        "Server ip in default turst group."
    ::= { es2226DhcpSnoopingDefaultGroupConf 5 }

es2226DhcpSnoopingLeaseList     OBJECT IDENTIFIER ::= { es2226DhcpSnooping 4 }

es2226DhcpSnoopingLeaseListDeleteAll OBJECT-TYPE
    SYNTAX         INTEGER(0|1)
    MAX-ACCESS     read-write
    STATUS         current
    DESCRIPTION
        "Delete all lease list.
         0 : None,
         1 : Delete All."
    ::= { es2226DhcpSnoopingLeaseList 1 }

es2226DhcpSnoopingLeaseListNumbers OBJECT-TYPE
    SYNTAX         INTEGER(0..512)
    MAX-ACCESS     read-only
    STATUS         current
    DESCRIPTION
        "Numbers of lease list."
    ::= { es2226DhcpSnoopingLeaseList 2 }

es2226DhcpSnoopingLeaseListTable  OBJECT-TYPE
    SYNTAX      SEQUENCE OF ES2226DhcpSnoopingLeaseListEntry
    MAX-ACCESS  not-accessible
    STATUS      current
    DESCRIPTION
        " "
    ::= { es2226DhcpSnoopingLeaseList 3 }

es2226DhcpSnoopingLeaseListEntry OBJECT-TYPE
    SYNTAX      ES2226DhcpSnoopingLeaseListEntry
    MAX-ACCESS  not-accessible
    STATUS      current
    DESCRIPTION
        "Entry(s) for DHCP snooping lease list table."
    INDEX {es2226DhcpSnoopingLeaseListIndex}
    ::= { es2226DhcpSnoopingLeaseListTable 1 }

ES2226DhcpSnoopingLeaseListEntry ::=
SEQUENCE {
    es2226DhcpSnoopingLeaseListIndex			INTEGER,
    es2226DhcpSnoopingLeaseListMac			DisplayString,
    es2226DhcpSnoopingLeaseListIp			IpAddress,
    es2226DhcpSnoopingLeaseListPort			INTEGER,
    es2226DhcpSnoopingLeaseListVid			INTEGER,
    es2226DhcpSnoopingLeaseListLease			DisplayString
}

es2226DhcpSnoopingLeaseListIndex  OBJECT-TYPE
    SYNTAX      INTEGER(1..512)
    MAX-ACCESS  not-accessible
    STATUS      current
    DESCRIPTION
        "The index of DHCP snooping lease list table."
    ::= { es2226DhcpSnoopingLeaseListEntry 1 }

es2226DhcpSnoopingLeaseListMac  OBJECT-TYPE
    SYNTAX      DisplayString
    MAX-ACCESS  read-only
    STATUS      current
    DESCRIPTION
        "The MAC of DHCP snooping lease list entry."
    ::= { es2226DhcpSnoopingLeaseListEntry 2 }

es2226DhcpSnoopingLeaseListIp  OBJECT-TYPE
    SYNTAX      IpAddress
    MAX-ACCESS  read-only
    STATUS      current
    DESCRIPTION
        "The IP of DHCP snooping lease list entry."
    ::= { es2226DhcpSnoopingLeaseListEntry 3 }

es2226DhcpSnoopingLeaseListPort  OBJECT-TYPE
    SYNTAX      INTEGER(1..26)
    MAX-ACCESS  read-only
    STATUS      current
    DESCRIPTION
        "The port of DHCP snooping lease list entry."
    ::= { es2226DhcpSnoopingLeaseListEntry 4 }

es2226DhcpSnoopingLeaseListVid  OBJECT-TYPE
    SYNTAX      INTEGER(1..4094)
    MAX-ACCESS  read-only
    STATUS      current
    DESCRIPTION
        "The vid of DHCP snooping lease list entry."
    ::= { es2226DhcpSnoopingLeaseListEntry 5 }

es2226DhcpSnoopingLeaseListLease  OBJECT-TYPE
    SYNTAX      DisplayString
    MAX-ACCESS  read-only
    STATUS      current
    DESCRIPTION
        "The lease of DHCP snooping lease list entry.
         (Day:Hour:Min:Sec)"
    ::= { es2226DhcpSnoopingLeaseListEntry 6 }

es2226DhcpSnoopingCounter     OBJECT IDENTIFIER ::= { es2226DhcpSnooping 5 }

es2226DhcpSnoopingCounterReset OBJECT-TYPE
    SYNTAX         INTEGER(0|1)
    MAX-ACCESS     read-write
    STATUS         current
    DESCRIPTION
        "Reset dhcp snooptin port counter.
         0 : None,
         1 : reset."
    ::= { es2226DhcpSnoopingCounter 1 }

es2226DhcpSnoopingCounterTable  OBJECT-TYPE
    SYNTAX      SEQUENCE OF ES2226DhcpSnoopingCounterEntry
    MAX-ACCESS  not-accessible
    STATUS      current
    DESCRIPTION
        " "
    ::= { es2226DhcpSnoopingCounter 2 }

es2226DhcpSnoopingCounterEntry OBJECT-TYPE
    SYNTAX      ES2226DhcpSnoopingCounterEntry
    MAX-ACCESS  not-accessible
    STATUS      current
    DESCRIPTION
        "Entry(s) for DHCP snooping port counter table."
    INDEX {es2226DhcpSnoopingCounterPortIndex}
    ::= { es2226DhcpSnoopingCounterTable 1 }

ES2226DhcpSnoopingCounterEntry ::=
SEQUENCE {
    es2226DhcpSnoopingCounterPortIndex			INTEGER,
    es2226DhcpSnoopingCounterDiscover			Counter32,
    es2226DhcpSnoopingCounterOffer			Counter32,
    es2226DhcpSnoopingCounterRequest			Counter32,
    es2226DhcpSnoopingCounterDecline			Counter32,
    es2226DhcpSnoopingCounterAck			Counter32,
    es2226DhcpSnoopingCounterNack			Counter32,
    es2226DhcpSnoopingCounterRelease			Counter32,
    es2226DhcpSnoopingCounterInform			Counter32
}

es2226DhcpSnoopingCounterPortIndex  OBJECT-TYPE
    SYNTAX      INTEGER(1..26)
    MAX-ACCESS  not-accessible
    STATUS      current
    DESCRIPTION
        "The port index of DHCP snooping port counter table."
    ::= { es2226DhcpSnoopingCounterEntry 1 }

es2226DhcpSnoopingCounterDiscover  OBJECT-TYPE
    SYNTAX      Counter32
    MAX-ACCESS  read-only
    STATUS      current
    DESCRIPTION
        "The discover of DHCP snooping port counter entry."
    ::= { es2226DhcpSnoopingCounterEntry 2 }

es2226DhcpSnoopingCounterOffer  OBJECT-TYPE
    SYNTAX      Counter32
    MAX-ACCESS  read-only
    STATUS      current
    DESCRIPTION
        "The offer of DHCP snooping port counter entry."
    ::= { es2226DhcpSnoopingCounterEntry 3 }

es2226DhcpSnoopingCounterRequest  OBJECT-TYPE
    SYNTAX      Counter32
    MAX-ACCESS  read-only
    STATUS      current
    DESCRIPTION
        "The request of DHCP snooping port counter entry."
    ::= { es2226DhcpSnoopingCounterEntry 4 }

es2226DhcpSnoopingCounterDecline  OBJECT-TYPE
    SYNTAX      Counter32
    MAX-ACCESS  read-only
    STATUS      current
    DESCRIPTION
        "The decline of DHCP snooping port counter entry."
    ::= { es2226DhcpSnoopingCounterEntry 5 }

es2226DhcpSnoopingCounterAck  OBJECT-TYPE
    SYNTAX      Counter32
    MAX-ACCESS  read-only
    STATUS      current
    DESCRIPTION
        "The ack of DHCP snooping port counter entry."
    ::= { es2226DhcpSnoopingCounterEntry 6 }

es2226DhcpSnoopingCounterNack  OBJECT-TYPE
    SYNTAX      Counter32
    MAX-ACCESS  read-only
    STATUS      current
    DESCRIPTION
        "The nack of DHCP snooping port counter entry."
    ::= { es2226DhcpSnoopingCounterEntry 7 }

es2226DhcpSnoopingCounterRelease  OBJECT-TYPE
    SYNTAX      Counter32
    MAX-ACCESS  read-only
    STATUS      current
    DESCRIPTION
        "The release of DHCP snooping port counter entry."
    ::= { es2226DhcpSnoopingCounterEntry 8 }

es2226DhcpSnoopingCounterInform  OBJECT-TYPE
    SYNTAX      Counter32
    MAX-ACCESS  read-only
    STATUS      current
    DESCRIPTION
        "The inform of DHCP snooping port counter entry."
    ::= { es2226DhcpSnoopingCounterEntry 9 }

es2226Dot1X        OBJECT IDENTIFIER ::= { es2226Produces 19 }

es2226Dot1XStateSetting      OBJECT IDENTIFIER ::= { es2226Dot1X 1 }

es2226RadiusServer1 OBJECT-TYPE
    SYNTAX         IpAddress
    MAX-ACCESS     read-write
    STATUS         current
    DESCRIPTION
        "Set radius server 1 ip"
    ::= { es2226Dot1XStateSetting 1 }

es2226Dot1XPort1 OBJECT-TYPE
    SYNTAX         INTEGER(1..65535)
    MAX-ACCESS     read-write
    STATUS         current
    DESCRIPTION
        "Set 802.1X port number"
    ::= { es2226Dot1XStateSetting 2 }

es2226RadiusServer2 OBJECT-TYPE
    SYNTAX         IpAddress
    MAX-ACCESS     read-write
    STATUS         current
    DESCRIPTION
        "Set radius server 2 ip"
    ::= { es2226Dot1XStateSetting 3 }

es2226Dot1XPort2 OBJECT-TYPE
    SYNTAX         INTEGER(1..65535)
    MAX-ACCESS     read-write
    STATUS         current
    DESCRIPTION
        "Set 802.1X port number"
    ::= { es2226Dot1XStateSetting 4 }

es2226SecretKey1  OBJECT-TYPE
    SYNTAX         DisplayString
    MAX-ACCESS     read-write
    STATUS         current
    DESCRIPTION
        "Set 802.1X secret key"
    ::= { es2226Dot1XStateSetting 5 }

es2226AccountingService  OBJECT-TYPE
    SYNTAX         INTEGER(0|1)
    MAX-ACCESS     read-write
    STATUS         current
    DESCRIPTION
        "Set 802.1X accounting service
         0 : disable
         1 : enable
        "
    ::= { es2226Dot1XStateSetting 6 }

es2226AccountingServer1  OBJECT-TYPE
    SYNTAX         IpAddress
    MAX-ACCESS     read-write
    STATUS         current
    DESCRIPTION
        "Set 802.1X accounting server 1"
    ::= { es2226Dot1XStateSetting 7 }

es2226AccountingPort1  OBJECT-TYPE
    SYNTAX         INTEGER(1..65535)
    MAX-ACCESS     read-write
    STATUS         current
    DESCRIPTION
        "Set 802.1X accounting port number"
    ::= { es2226Dot1XStateSetting 8 }

es2226AccountingServer2  OBJECT-TYPE
    SYNTAX         IpAddress
    MAX-ACCESS     read-write
    STATUS         current
    DESCRIPTION
        "Set 802.1X accounting server 2"
    ::= { es2226Dot1XStateSetting 9 }

es2226AccountingPort2  OBJECT-TYPE
    SYNTAX         INTEGER(1..65535)
    MAX-ACCESS     read-write
    STATUS         current
    DESCRIPTION
        "Set 802.1X accounting port number"
    ::= { es2226Dot1XStateSetting 10 }

es2226SecretKey2  OBJECT-TYPE
    SYNTAX         DisplayString
    MAX-ACCESS     read-write
    STATUS         current
    DESCRIPTION
        "Set 802.1X secret key"
    ::= { es2226Dot1XStateSetting 11 }

es2226Dot1XPortSecurityManagement      OBJECT IDENTIFIER ::= { es2226Dot1X 2 }

es2226Dot1XPortSecurityTable  OBJECT-TYPE
    SYNTAX      SEQUENCE OF ES2226Dot1XPortSecurityEntry
    MAX-ACCESS  not-accessible
    STATUS      current
    DESCRIPTION
        " "
    ::= { es2226Dot1XPortSecurityManagement 1 }

es2226Dot1XPortSecurityEntry OBJECT-TYPE
    SYNTAX      ES2226Dot1XPortSecurityEntry
    MAX-ACCESS  not-accessible
    STATUS      current
    DESCRIPTION
        "Entry(s) for 802.1x port security management table."
    INDEX {es2226Dot1XPortSecurityPortIndex}
    ::= { es2226Dot1XPortSecurityTable 1 }

ES2226Dot1XPortSecurityEntry ::=
SEQUENCE {
    es2226Dot1XPortSecurityPortIndex				INTEGER,
    es2226Dot1XPortSecurityMode   				INTEGER,
    es2226Dot1XPortSecurityPortControl  			INTEGER,
    es2226Dot1XPortSecurityReAuthMax				INTEGER,
    es2226Dot1XPortSecurityTxPeriod				INTEGER,
    es2226Dot1XPortSecurityQuietPeriod				INTEGER,
    es2226Dot1XPortSecurityReAuthEnabled			INTEGER,
    es2226Dot1XPortSecurityReAuthPeriod				INTEGER,
    es2226Dot1XPortSecurityMaxRequest				INTEGER,
    es2226Dot1XPortSecuritySuppTimeout				INTEGER,
    es2226Dot1XPortSecurityServerTimeout			INTEGER,
    es2226Dot1XPortSecurityStatus				DisplayString
}

es2226Dot1XPortSecurityPortIndex  OBJECT-TYPE
    SYNTAX      INTEGER(1..26)
    MAX-ACCESS  not-accessible
    STATUS      current
    DESCRIPTION
        "The port index of 802.1x port security."
    ::= { es2226Dot1XPortSecurityEntry 1 }

es2226Dot1XPortSecurityMode  OBJECT-TYPE
    SYNTAX      INTEGER(0..2)
    MAX-ACCESS  read-write
    STATUS      current
    DESCRIPTION
        "The mode of 802.1x port security.
         0 : Disable,
         1 : Normal,
         2 : Advanced 802.1X
        "
    ::= { es2226Dot1XPortSecurityEntry 2 }

es2226Dot1XPortSecurityPortControl  OBJECT-TYPE
    SYNTAX      INTEGER(0..2)
    MAX-ACCESS  read-write
    STATUS      current
    DESCRIPTION
        "The port control of 802.1x port security.
	 0 : ForceUnauthorized,
	 1 : ForceAuthorized,
	 2 : Auto
        "
    ::= { es2226Dot1XPortSecurityEntry 3 }

es2226Dot1XPortSecurityReAuthMax  OBJECT-TYPE
    SYNTAX      INTEGER(1..10)
    MAX-ACCESS  read-write
    STATUS      current
    DESCRIPTION
        "The reAuthMax(1~10) of 802.1x port security."
    ::= { es2226Dot1XPortSecurityEntry 4 }

es2226Dot1XPortSecurityTxPeriod  OBJECT-TYPE
    SYNTAX      INTEGER(1..65535)
    MAX-ACCESS  read-write
    STATUS      current
    DESCRIPTION
        "The txPeriod(1~65535) of 802.1x port security."
    ::= { es2226Dot1XPortSecurityEntry 5 }

es2226Dot1XPortSecurityQuietPeriod  OBJECT-TYPE
    SYNTAX      INTEGER(0..65535)
    MAX-ACCESS  read-write
    STATUS      current
    DESCRIPTION
        "The quiet period(0~65535) of 802.1x port security."
    ::= { es2226Dot1XPortSecurityEntry 6 }

es2226Dot1XPortSecurityReAuthEnabled  OBJECT-TYPE
    SYNTAX      INTEGER(0|1)
    MAX-ACCESS  read-write
    STATUS      current
    DESCRIPTION
        "The reAuthEnabled of 802.1x port security.
         0 : off,
         1 : on.
        "
    ::= { es2226Dot1XPortSecurityEntry 7 }

es2226Dot1XPortSecurityReAuthPeriod  OBJECT-TYPE
    SYNTAX      INTEGER(1..65535)
    MAX-ACCESS  read-write
    STATUS      current
    DESCRIPTION
        "The reAuthPeriod(1~65535) of 802.1x port security."
    ::= { es2226Dot1XPortSecurityEntry 8 }

es2226Dot1XPortSecurityMaxRequest  OBJECT-TYPE
    SYNTAX      INTEGER(1..10)
    MAX-ACCESS  read-write
    STATUS      current
    DESCRIPTION
        "The max.request(1~10) of 802.1x port security."
    ::= { es2226Dot1XPortSecurityEntry 9 }

es2226Dot1XPortSecuritySuppTimeout  OBJECT-TYPE
    SYNTAX      INTEGER(1..255)
    MAX-ACCESS  read-write
    STATUS      current
    DESCRIPTION
        "The suppTimeout(1~255) of 802.1x port security."
    ::= { es2226Dot1XPortSecurityEntry 10 }

es2226Dot1XPortSecurityServerTimeout  OBJECT-TYPE
    SYNTAX      INTEGER(1..255)
    MAX-ACCESS  read-write
    STATUS      current
    DESCRIPTION
        "The server timeout(1~255) of 802.1x port security."
    ::= { es2226Dot1XPortSecurityEntry 11 }

es2226Dot1XPortSecurityStatus  OBJECT-TYPE
    SYNTAX      DisplayString
    MAX-ACCESS  read-only
    STATUS      current
    DESCRIPTION
        "The status of 802.1x port security."
    ::= { es2226Dot1XPortSecurityEntry 12 }

es2226TrapEntry        OBJECT IDENTIFIER ::= { es2226Produces 20 }

es2226ModuleInserted NOTIFICATION-TYPE
    OBJECTS { ifIndex }
    STATUS    current
    DESCRIPTION
        "Send the trap when a module is inserted to the system. The OID value means
         the port number."
    ::= { es2226TrapEntry 1 }

es2226ModuleRemoved NOTIFICATION-TYPE
    OBJECTS { ifIndex }
    STATUS    current
    DESCRIPTION
        "Send the trap when a module is removed from the system. The OID value means
         the port number."
    ::= { es2226TrapEntry 2 }

es2226DualMediaSwapped NOTIFICATION-TYPE
    OBJECTS { ifIndex }
    STATUS    current
    DESCRIPTION
        "Send the trap when the dual media port changed. The OID value means the port number."
    ::= { es2226TrapEntry 3 }

es2226LoopDetected NOTIFICATION-TYPE
    OBJECTS { ifIndex }
    STATUS    current
    DESCRIPTION
        "Send the trap when loop condition has been detected. The OID value means the port number."
    ::= { es2226TrapEntry 4 }

es2226IpMacBindOffered NOTIFICATION-TYPE
    OBJECTS { ipmacbind }
    STATUS    current
    DESCRIPTION
        "Send the trap when a pair of IP-MAC binding is offered."
    ::= { es2226TrapEntry 5 }

es2226IpMacBindReleased NOTIFICATION-TYPE
    OBJECTS { ipmacbind }
    STATUS    current
    DESCRIPTION
        "Send the trap when a pair of IP-MAC binding is released."
    ::= { es2226TrapEntry 6 }

es2226ARPInspectionDetected NOTIFICATION-TYPE
    OBJECTS { arpinspect }
    STATUS    current
    DESCRIPTION
        "Send the trap when ARP inspection detected."
    ::= { es2226TrapEntry 7 }

es2226StpStateDisabled NOTIFICATION-TYPE
    STATUS      current
    DESCRIPTION
       "Send the trap when the operational state of STP is from enabled to disabled. "
    ::= { es2226TrapEntry 100 }

es2226StpStateEnabled NOTIFICATION-TYPE
    STATUS      current
    DESCRIPTION
       "Send the trap when the operational state of STP is from disabled to enabled. "
    ::= { es2226TrapEntry 101 }

es2226StpTopologyChanged NOTIFICATION-TYPE
    OBJECTS { ifIndex }
    STATUS      current
    DESCRIPTION
       "Send the trap when RSTP determines a port should enter the FORWARDING state
        (a topology change occurs). The OID value is the ifIndex of the port that
        produces the topology change."
    ::= { es2226TrapEntry 102 }

es2226RmonRisingAlarm NOTIFICATION-TYPE
    STATUS      current
    DESCRIPTION
       "Send the trap when an RMON rising alarm happened. The OID value is the value
        of another OID variable sampled by the RMON Alarm Group that exceeds its
        own RisingThreshold "
    ::= { es2226TrapEntry 110 }

es2226RmonFallingAlarm NOTIFICATION-TYPE
    STATUS      current
    DESCRIPTION
           "Send the trap when an RMON falling alarm happened. The OID value is the value
        of another OID variable sampled by the RMON Alarm Group that is smaller than its
        own FallingThreshold "
    ::= { es2226TrapEntry 111 }

es2226LacpStateDisabled NOTIFICATION-TYPE
    OBJECTS {ifIndex, groupId}
    STATUS      current
    DESCRIPTION
       "Send the trap when the operational state of LACP is from enabled to disabled.
        The OID value means the disabled Group ID."
    ::= { es2226TrapEntry 120 }

es2226LacpStateEnabled NOTIFICATION-TYPE
    OBJECTS {ifIndex, groupId}
    STATUS      current
    DESCRIPTION
       "Send the trap when the operational state of LACP is from disabled to enabled.
        The OID value means the disabled Group ID."
    ::= { es2226TrapEntry 121 }

es2226LacpPortAdded NOTIFICATION-TYPE
    OBJECTS   { ifIndex, actorkey, partnerkey }
    STATUS      current
    DESCRIPTION
       "Send the trap when the state of port is in 'trunk ready'."
    ::= { es2226TrapEntry 123 }

es2226LacpPortTrunkFailure NOTIFICATION-TYPE
    OBJECTS   { ifIndex, actorkey, partnerkey}
    STATUS      current
    DESCRIPTION
       "Send the trap when one port is not able to be aggregated
        due to duplex-mode of the port. "
    ::= { es2226TrapEntry 124 }

es2226GvrpStateDisabled NOTIFICATION-TYPE
    STATUS      current
    DESCRIPTION
       "Send the trap when the operational state of GVRP is from enabled to disabled. "
    ::= { es2226TrapEntry 140 }

es2226GvrpStateEnabled NOTIFICATION-TYPE
    STATUS      current
    DESCRIPTION
       "Send the trap when the operational state of LACP is from disabled to enabled. "
    ::= { es2226TrapEntry 141 }

es2226VlanPortBaseEnabled NOTIFICATION-TYPE
    STATUS      current
    DESCRIPTION
       "Send the trap when the operational state of vlan is changed to port-based vlan."
    ::= { es2226TrapEntry 151 }

es2226VlanTagBaseEnabled NOTIFICATION-TYPE
    STATUS      current
    DESCRIPTION
       "Send the trap when the operational state of vlan is changed to tag-based vlan."
    ::= { es2226TrapEntry 152 }

es2226VlanMetroBaseEnabled NOTIFICATION-TYPE
    STATUS      current
    DESCRIPTION
       "Send the trap when the operational state of vlan is changed to metro-based vlan."
    ::= { es2226TrapEntry 153 }

es2226UserLogin NOTIFICATION-TYPE
    OBJECTS   {username}
    STATUS      current
    DESCRIPTION
       "Send the trap when one user logins the system."
    ::= { es2226TrapEntry 200 }

es2226UserLogout NOTIFICATION-TYPE
    OBJECTS   {username}
    STATUS      current
    DESCRIPTION
       "Send the trap when one user logouts the system."
    ::= { es2226TrapEntry 201 }

es2226TrapVariable  OBJECT IDENTIFIER ::= { es2226Produces 21 }

username OBJECT-TYPE
    SYNTAX      DisplayString
    MAX-ACCESS  read-only
    STATUS      current
    DESCRIPTION
        "System account name."
    ::= { es2226TrapVariable 1 }

groupId OBJECT-TYPE
    SYNTAX      INTEGER(1..8)
    MAX-ACCESS  read-only
    STATUS      current
    DESCRIPTION
        "The Trunk group ID of LACP."
    ::= { es2226TrapVariable 2 }

actorkey OBJECT-TYPE
    SYNTAX  INTEGER(1..2147483647)
    MAX-ACCESS  read-only
    STATUS      current
    DESCRIPTION
        "This is the actor key information for LACP."
    ::= { es2226TrapVariable 3 }

partnerkey OBJECT-TYPE
    SYNTAX  INTEGER(1..2147483647)
    MAX-ACCESS  read-only
    STATUS      current
    DESCRIPTION
        "This is the partner key information for LACP."
    ::= { es2226TrapVariable 4 }

uplink OBJECT-TYPE
    SYNTAX  DisplayString
    MAX-ACCESS  read-only
    STATUS      current
    DESCRIPTION
        "Uplink port(s) in the metro-mode vlan."
    ::= { es2226TrapVariable 5 }

ipmacbind OBJECT-TYPE
    SYNTAX      DisplayString
    MAX-ACCESS  read-only
    STATUS      current
    DESCRIPTION
        "IP-MAC Binding value. Format as mac:00:40:c7:00:00:01,ip:192.168.2.3,port:20
         00:40:c7:00:00:01 is the mac address;
         192.168.2.3 is the binding ip address;
         port:20 is the port, e.g 20"
    ::= { es2226TrapVariable 6 }

arpinspect OBJECT-TYPE
    SYNTAX      DisplayString
    MAX-ACCESS  read-only
    STATUS      current
    DESCRIPTION
        "ARP Inspection detected.
         Format as mac:00:40:c7:00:00:01, port:20, Unknown Mac/IP."
    ::= { es2226TrapVariable 7 }

es2226Acl       OBJECT IDENTIFIER ::= { es2226Produces 22 }

es2226HighAcl      OBJECT IDENTIFIER ::= { es2226Acl 1 }

es2226HighAclCreatStatus OBJECT-TYPE
    SYNTAX         INTEGER(0|1)
    MAX-ACCESS     read-write
    STATUS         current
    DESCRIPTION
        "Create a new high-acl
         0 : None,
         1 : Create a high-acl temp entry
        "
    ::= { es2226HighAcl 1 }

es2226HighAclNumbers OBJECT-TYPE
    SYNTAX         INTEGER(0..128)
    MAX-ACCESS     read-only
    STATUS         current
    DESCRIPTION
        "Numbers of high-acl table."
    ::= { es2226HighAcl 2 }

es2226HighAclTable  OBJECT-TYPE
    SYNTAX      SEQUENCE OF ES2226HighAclEntry
    MAX-ACCESS  not-accessible
    STATUS      current
    DESCRIPTION
        " "
    ::= { es2226HighAcl 3 }

es2226HighAclEntry OBJECT-TYPE
    SYNTAX      ES2226HighAclEntry
    MAX-ACCESS  not-accessible
    STATUS      current
    DESCRIPTION
        "Entry(s) for high-acl table."
    INDEX {es2226HighAclIndex}
    ::= { es2226HighAclTable 1 }

ES2226HighAclEntry ::=
SEQUENCE {
    es2226HighAclIndex						INTEGER,
    es2226HighAclName   					DisplayString,
    es2226HighAclIngressPortMap		  			DisplayString,
    es2226HighAclSMacFilter					DisplayString,
    es2226HighAclDMacFilter					DisplayString,
    es2226HighAclVlanType					INTEGER,
    es2226HighAclTagVid						INTEGER,
    es2226HighAclTagPriority					INTEGER,
    es2226HighAclEthernetType					DisplayString,
    es2226HighAclIPv4Protocol					INTEGER,
    es2226HighAclIPv4ToS					DisplayString,
    es2226HighAclIPv4TTLRange					INTEGER,
    es2226HighAclIPv4DA						IpAddress,
    es2226HighAclIPv4DAMask					IpAddress,
    es2226HighAclIPv4SA						IpAddress,
    es2226HighAclIPv4SAMask					IpAddress,
    es2226HighAclL4DestinationPort				INTEGER,
    es2226HighAclL4SourcePort					INTEGER,
    es2226HighAclActionIBForwardDecision			INTEGER,
    es2226HighAclActionIBForwardMap				INTEGER,
    es2226HighAclActionIBModifyDSCPPacket			INTEGER,
    es2226HighAclActionIBModifyDSCPValue			INTEGER,
    es2226HighAclActionOBForwardDecision			INTEGER,
    es2226HighAclActionOBForwardMap				INTEGER,
    es2226HighAclActionOBModifyDSCPPacket			INTEGER,
    es2226HighAclActionOBModifyDSCPValue			INTEGER,
    es2226HighAclActionModifyDot1PPacket			INTEGER,
    es2226HighAclActionModifyDot1PValue				INTEGER,
    es2226HighAclActionModifyQoSPacket				INTEGER,
    es2226HighAclActionModifyQoSValue				INTEGER,
    es2226HighAclRateMeter					INTEGER,
    es2226HighAclRowStatus					INTEGER
}

es2226HighAclIndex  OBJECT-TYPE
    SYNTAX      INTEGER(1..128)
    MAX-ACCESS  not-accessible
    STATUS      current
    DESCRIPTION
        "The entry index of high-acl table."
    ::= { es2226HighAclEntry 1 }

es2226HighAclName OBJECT-TYPE
    SYNTAX         DisplayString
    MAX-ACCESS     read-write
    STATUS         current
    DESCRIPTION
        "The name of high-acl entry."
    ::= { es2226HighAclEntry 2 }

es2226HighAclIngressPortMap OBJECT-TYPE
    SYNTAX         DisplayString
    MAX-ACCESS     read-write
    STATUS         current
    DESCRIPTION
        "The ingress port map of high-acl entry.
         port range: syntax: 1,5-7, available from 1 to 26, 0 for any.
        "
    ::= { es2226HighAclEntry 3 }

es2226HighAclSMacFilter OBJECT-TYPE
    SYNTAX         DisplayString
    MAX-ACCESS     read-write
    STATUS         current
    DESCRIPTION
        "The source mac filter of high-acl entry."
    ::= { es2226HighAclEntry 4 }

es2226HighAclDMacFilter OBJECT-TYPE
    SYNTAX         DisplayString
    MAX-ACCESS     read-write
    STATUS         current
    DESCRIPTION
        "The destination mac filter of high-acl entry."
    ::= { es2226HighAclEntry 5 }

es2226HighAclVlanType OBJECT-TYPE
    SYNTAX         INTEGER(0|1)
    MAX-ACCESS     read-write
    STATUS         current
    DESCRIPTION
        "The vlan type of high-acl entry.
         0 : Any,
         1 : Tag-Based Vlan.
        "
    ::= { es2226HighAclEntry 6 }

es2226HighAclTagVid OBJECT-TYPE
    SYNTAX         INTEGER(0..4094)
    MAX-ACCESS     read-write
    STATUS         current
    DESCRIPTION
        "The tag-based vlan vid of high-acl entry.
         VLAN ID, form 1 to 4094, 0 for priority tag.
        "
    ::= { es2226HighAclEntry 7 }


es2226HighAclTagPriority OBJECT-TYPE
    SYNTAX         INTEGER(0..7)
    MAX-ACCESS     read-write
    STATUS         current
    DESCRIPTION
        "The tag priority(0~7) of high-acl entry."
    ::= { es2226HighAclEntry 8 }

es2226HighAclEthernetType OBJECT-TYPE
    SYNTAX         DisplayString(SIZE(0..4))
    MAX-ACCESS     read-write
    STATUS         current
    DESCRIPTION
        "The ethernet type of high-acl entry.
	 Ethernet type, format: 0806 (in hexadecimal format).
	 Example: IPv4 for 0800, ARP for 0806, Any for 0000.
        "
    ::= { es2226HighAclEntry 9 }

es2226HighAclIPv4Protocol OBJECT-TYPE
    SYNTAX         INTEGER(0..255)
    MAX-ACCESS     read-write
    STATUS         current
    DESCRIPTION
        "The IPv4 protocol of high-acl entry.
	 IPv4 protocol, from 0 to 255.
	 Example: ICMP for 1, UDP for 17, TCP for 6.
        "
    ::= { es2226HighAclEntry 10 }

es2226HighAclIPv4ToS OBJECT-TYPE
    SYNTAX         DisplayString(SIZE(0..2))
    MAX-ACCESS     read-write
    STATUS         current
    DESCRIPTION
        "The IPv4 ToS of high-acl entry.
         IPv4 TOS field, from 00 to ff (in hexadecimal format).
        "
    ::= { es2226HighAclEntry 11 }

es2226HighAclIPv4TTLRange OBJECT-TYPE
    SYNTAX         INTEGER(0..3)
    MAX-ACCESS     read-write
    STATUS         current
    DESCRIPTION
        "The IPv4 TTL Range of high-acl entry.
	 0 : 0,
	 1 : 1,
	 2 : 2~254,
	 3 : 255.
        "
    ::= { es2226HighAclEntry 12 }

es2226HighAclIPv4DA OBJECT-TYPE
    SYNTAX         IpAddress
    MAX-ACCESS     read-write
    STATUS         current
    DESCRIPTION
        "The IPv4 destination Address value of high-acl entry."
    ::= { es2226HighAclEntry 13 }

es2226HighAclIPv4DAMask OBJECT-TYPE
    SYNTAX         IpAddress
    MAX-ACCESS     read-write
    STATUS         current
    DESCRIPTION
        "The IPv4 destination Address mask value of high-acl entry."
    ::= { es2226HighAclEntry 14 }

es2226HighAclIPv4SA OBJECT-TYPE
    SYNTAX         IpAddress
    MAX-ACCESS     read-write
    STATUS         current
    DESCRIPTION
        "The IPv4 Source Address value of high-acl entry."
    ::= { es2226HighAclEntry 15 }

es2226HighAclIPv4SAMask OBJECT-TYPE
    SYNTAX         IpAddress
    MAX-ACCESS     read-write
    STATUS         current
    DESCRIPTION
        "The IPv4 Source Address mask value of high-acl entry."
    ::= { es2226HighAclEntry 16 }

es2226HighAclL4DestinationPort OBJECT-TYPE
    SYNTAX         INTEGER(0..65535)
    MAX-ACCESS     read-write
    STATUS         current
    DESCRIPTION
        "The L4 destination port number of high-acl entry.
         port: IPv4 L4 destination port, from 0 to 65535
        "
    ::= { es2226HighAclEntry 17 }

es2226HighAclL4SourcePort OBJECT-TYPE
    SYNTAX         INTEGER(0..65535)
    MAX-ACCESS     read-write
    STATUS         current
    DESCRIPTION
        "The L4 source port number of high-acl entry.
         port: IPv4 L4 source port, from 0 to 65535
        "
    ::= { es2226HighAclEntry 18 }

es2226HighAclActionIBForwardDecision OBJECT-TYPE
    SYNTAX         INTEGER(0..3)
    MAX-ACCESS     read-write
    STATUS         current
    DESCRIPTION
        "The forward decision in in-Band.
         0 : No change,
         1 : Use new forward map,
         2 : ORed with new map,
         3 : Explicit actions
        "
    ::= { es2226HighAclEntry 19 }

es2226HighAclActionIBForwardMap OBJECT-TYPE
    SYNTAX         INTEGER(0..26)
    MAX-ACCESS     read-write
    STATUS         current
    DESCRIPTION
        "If es2226HighAclActionIBForwardDecision as 0 then
            0 : As ARL map.
         If es2226HighAclActionIBForwardDecision as 1 or 2 then
	    0 : All Linked-Port,
	    1~26 : Port 1 ~ Port 26
	 If  es2226HighAclActionIBForwardDecision as 3 then
	    0 : As ARL map,
	    1 : As ARL map and copy to mirror port,
	    2 : Drop,
	    3 : Forward to mirror port.
    	"
    ::= { es2226HighAclEntry 20 }

es2226HighAclActionIBModifyDSCPPacket OBJECT-TYPE
    SYNTAX         INTEGER(0|1)
    MAX-ACCESS     read-write
    STATUS         current
    DESCRIPTION
        "Modify DSCP packet value in in-Band.
         0 : Any,
         1 : Specific.
        "
    ::= { es2226HighAclEntry 21 }

es2226HighAclActionIBModifyDSCPValue OBJECT-TYPE
    SYNTAX         INTEGER(0..63)
    MAX-ACCESS     read-write
    STATUS         current
    DESCRIPTION
        "Be used by es2226HighAclActionIBModifyDSCPPacket as 1.
         New DSCP field value, from 0 to 63"
    ::= { es2226HighAclEntry 22 }

es2226HighAclActionOBForwardDecision OBJECT-TYPE
    SYNTAX         INTEGER(0..3)
    MAX-ACCESS     read-write
    STATUS         current
    DESCRIPTION
        "The forward decision in out-Band.
         0 : No change,
         1 : Use new forward map,
         2 : ORed with new map,
         3 : Explicit actions
        "
    ::= { es2226HighAclEntry 23 }

es2226HighAclActionOBForwardMap OBJECT-TYPE
    SYNTAX         INTEGER(0..26)
    MAX-ACCESS     read-write
    STATUS         current
    DESCRIPTION
        "If es2226HighAclActionOBForwardDecision as 0
            0 : As ARL map.
         If es2226HighAclActionOBForwardDecision as 1 or 2 then
	    0 : All Linked-Port,
	    1~26 : Port 1 ~ Port 26
	 If es2226HighAclActionOBForwardDecision as 3 then
	    0 : As ARL map,
	    1 : As ARL map and copy to mirror port ,
	    2 : Drop,
	    3 : Forward to mirror port.
    	"
    ::= { es2226HighAclEntry 24 }

es2226HighAclActionOBModifyDSCPPacket OBJECT-TYPE
    SYNTAX         INTEGER(0|1)
    MAX-ACCESS     read-write
    STATUS         current
    DESCRIPTION
        "Modify DSCP packet value in out-Band.
         0 : Any,
         1 : Specific.
        "
    ::= { es2226HighAclEntry 25 }

es2226HighAclActionOBModifyDSCPValue OBJECT-TYPE
    SYNTAX         INTEGER(0..63)
    MAX-ACCESS     read-write
    STATUS         current
    DESCRIPTION
        "Be used by es2226HighAclActionOBModifyDSCPPacket as 1.
         New DSCP field value, from 0 to 63"
    ::= { es2226HighAclEntry 26 }

es2226HighAclActionModifyDot1PPacket OBJECT-TYPE
    SYNTAX         INTEGER(0|1)
    MAX-ACCESS     read-write
    STATUS         current
    DESCRIPTION
        "Modify 802.1P packet value.
         0 : Any,
         1 : Specific.
        "
    ::= { es2226HighAclEntry 27 }

es2226HighAclActionModifyDot1PValue OBJECT-TYPE
    SYNTAX         INTEGER(0..7)
    MAX-ACCESS     read-write
    STATUS         current
    DESCRIPTION
        "Be used by es2226HighAclActionModifyDot1PPacket as 1.
         New 802.1P field value, from 0 to 7"
    ::= { es2226HighAclEntry 28 }

es2226HighAclActionModifyQoSPacket OBJECT-TYPE
    SYNTAX         INTEGER(0|1)
    MAX-ACCESS     read-write
    STATUS         current
    DESCRIPTION
        "Modify QoS packet value.
         0 : Any,
         1 : Specific.
        "
    ::= { es2226HighAclEntry 29 }

es2226HighAclActionModifyQoSValue OBJECT-TYPE
    SYNTAX         INTEGER(0..3)
    MAX-ACCESS     read-write
    STATUS         current
    DESCRIPTION
        "Be used by es2226HighAclActionModifyQoSPacket as 1.
         New QoS field value, from 0 to 3"
    ::= { es2226HighAclEntry 30 }

es2226HighAclRateMeter OBJECT-TYPE
    SYNTAX         INTEGER(64..1024000)
    MAX-ACCESS     read-write
    STATUS         current
    DESCRIPTION
        "The rate meter(64..1024000) of high-acl entry."
    ::= { es2226HighAclEntry 31 }

es2226HighAclRowStatus  OBJECT-TYPE
    SYNTAX      INTEGER(1..3)
    MAX-ACCESS  read-write
    STATUS      current
    DESCRIPTION
        "The row status of high-acl entry.
         1 : active,
         2 : not-inService,
         3 : delete
        "
    ::= { es2226HighAclEntry 32 }

es2226LowAcl      OBJECT IDENTIFIER ::= { es2226Acl 2 }

es2226LowAclCreatStatus OBJECT-TYPE
    SYNTAX         INTEGER(0|1)
    MAX-ACCESS     read-write
    STATUS         current
    DESCRIPTION
        "Create a new low-acl
         0 : None,
         1 : Create a low-acl temp entry
        "
    ::= { es2226LowAcl 1 }

es2226LowAclNumbers OBJECT-TYPE
    SYNTAX         INTEGER(0..128)
    MAX-ACCESS     read-only
    STATUS         current
    DESCRIPTION
        "Numbers of low-acl table."
    ::= { es2226LowAcl 2 }

es2226LowAclTable  OBJECT-TYPE
    SYNTAX      SEQUENCE OF ES2226LowAclEntry
    MAX-ACCESS  not-accessible
    STATUS      current
    DESCRIPTION
        " "
    ::= { es2226LowAcl 3 }

es2226LowAclEntry OBJECT-TYPE
    SYNTAX      ES2226LowAclEntry
    MAX-ACCESS  not-accessible
    STATUS      current
    DESCRIPTION
        "Entry(s) for Low-acl table."
    INDEX {es2226LowAclIndex}
    ::= { es2226LowAclTable 1 }

ES2226LowAclEntry ::=
SEQUENCE {
    es2226LowAclIndex						INTEGER,
    es2226LowAclName   						DisplayString,
    es2226LowAclIngressPortMap		  			DisplayString,
    es2226LowAclSMacFilter					DisplayString,
    es2226LowAclDMacFilter					DisplayString,
    es2226LowAclVlanType					INTEGER,
    es2226LowAclTagVid						INTEGER,
    es2226LowAclTagPriority					INTEGER,
    es2226LowAclEthernetType					DisplayString,
    es2226LowAclIPv4Protocol					INTEGER,
    es2226LowAclIPv4ToS						DisplayString,
    es2226LowAclIPv4TTLRange					INTEGER,
    es2226LowAclIPv4DA						IpAddress,
    es2226LowAclIPv4DAMask					IpAddress,
    es2226LowAclIPv4SA						IpAddress,
    es2226LowAclIPv4SAMask					IpAddress,
    es2226LowAclL4DestinationPort				INTEGER,
    es2226LowAclL4SourcePort					INTEGER,
    es2226LowAclActionIBForwardDecision				INTEGER,
    es2226LowAclActionIBForwardMap				INTEGER,
    es2226LowAclActionIBModifyDSCPPacket			INTEGER,
    es2226LowAclActionIBModifyDSCPValue				INTEGER,
    es2226LowAclActionOBForwardDecision				INTEGER,
    es2226LowAclActionOBForwardMap				INTEGER,
    es2226LowAclActionOBModifyDSCPPacket			INTEGER,
    es2226LowAclActionOBModifyDSCPValue				INTEGER,
    es2226LowAclActionModifyDot1PPacket				INTEGER,
    es2226LowAclActionModifyDot1PValue				INTEGER,
    es2226LowAclActionModifyQoSPacket				INTEGER,
    es2226LowAclActionModifyQoSValue				INTEGER,
    es2226LowAclRateMeter					INTEGER,
    es2226LowAclRowStatus					INTEGER
}

es2226LowAclIndex  OBJECT-TYPE
    SYNTAX      INTEGER(1..128)
    MAX-ACCESS  not-accessible
    STATUS      current
    DESCRIPTION
        "The entry index of Low-acl table."
    ::= { es2226LowAclEntry 1 }

es2226LowAclName OBJECT-TYPE
    SYNTAX         DisplayString
    MAX-ACCESS     read-write
    STATUS         current
    DESCRIPTION
        "The name of low-acl entry."
    ::= { es2226LowAclEntry 2 }

es2226LowAclIngressPortMap OBJECT-TYPE
    SYNTAX         DisplayString
    MAX-ACCESS     read-write
    STATUS         current
    DESCRIPTION
        "The ingress port map of Low-acl entry.
         port range: syntax: 1,5-7, available from 1 to 26, 0 for any.
        "
    ::= { es2226LowAclEntry 3 }

es2226LowAclSMacFilter OBJECT-TYPE
    SYNTAX         DisplayString
    MAX-ACCESS     read-write
    STATUS         current
    DESCRIPTION
        "The source mac filter of low-acl entry."
    ::= { es2226LowAclEntry 4 }

es2226LowAclDMacFilter OBJECT-TYPE
    SYNTAX         DisplayString
    MAX-ACCESS     read-write
    STATUS         current
    DESCRIPTION
        "The destination mac filter of low-acl entry."
    ::= { es2226LowAclEntry 5 }

es2226LowAclVlanType OBJECT-TYPE
    SYNTAX         INTEGER(0|1)
    MAX-ACCESS     read-write
    STATUS         current
    DESCRIPTION
        "The vlan type of low-acl entry.
         0 : Any,
         1 : Tag-Based Vlan.
        "
    ::= { es2226LowAclEntry 6 }

es2226LowAclTagVid OBJECT-TYPE
    SYNTAX         INTEGER(0..4094)
    MAX-ACCESS     read-write
    STATUS         current
    DESCRIPTION
        "The tag-based vlan vid of low-acl entry.
         VLAN ID, form 1 to 4094, 0 for priority tag.
        "
    ::= { es2226LowAclEntry 7 }


es2226LowAclTagPriority OBJECT-TYPE
    SYNTAX         INTEGER(0..7)
    MAX-ACCESS     read-write
    STATUS         current
    DESCRIPTION
        "The tag priority(0~7) of low-acl entry."
    ::= { es2226LowAclEntry 8 }

es2226LowAclEthernetType OBJECT-TYPE
    SYNTAX         DisplayString(SIZE(0..4))
    MAX-ACCESS     read-write
    STATUS         current
    DESCRIPTION
        "The ethernet type of low-acl entry.
	 Ethernet type, format: 0806 (in hexadecimal format).
	 Example: IPv4 for 0800, ARP for 0806, Any for 0000.
        "
    ::= { es2226LowAclEntry 9 }

es2226LowAclIPv4Protocol OBJECT-TYPE
    SYNTAX         INTEGER(0..255)
    MAX-ACCESS     read-write
    STATUS         current
    DESCRIPTION
        "The IPv4 protocol of low-acl entry.
	 IPv4 protocol, from 0 to 255.
	 Example: ICMP for 1, UDP for 17, TCP for 6.
        "
    ::= { es2226LowAclEntry 10 }

es2226LowAclIPv4ToS OBJECT-TYPE
    SYNTAX         DisplayString(SIZE(0..2))
    MAX-ACCESS     read-write
    STATUS         current
    DESCRIPTION
        "The IPv4 ToS of low-acl entry.
         IPv4 TOS field, from 00 to ff (in hexadecimal format).
        "
    ::= { es2226LowAclEntry 11 }

es2226LowAclIPv4TTLRange OBJECT-TYPE
    SYNTAX         INTEGER(0..3)
    MAX-ACCESS     read-write
    STATUS         current
    DESCRIPTION
        "The IPv4 TTL Range of low-acl entry.
	 0 : 0,
	 1 : 1,
	 2 : 2~254,
	 3 : 255.
        "
    ::= { es2226LowAclEntry 12 }

es2226LowAclIPv4DA OBJECT-TYPE
    SYNTAX         IpAddress
    MAX-ACCESS     read-write
    STATUS         current
    DESCRIPTION
        "The IPv4 destination Address value of low-acl entry."
    ::= { es2226LowAclEntry 13 }

es2226LowAclIPv4DAMask OBJECT-TYPE
    SYNTAX         IpAddress
    MAX-ACCESS     read-write
    STATUS         current
    DESCRIPTION
        "The IPv4 destination Address mask value of low-acl entry."
    ::= { es2226LowAclEntry 14 }

es2226LowAclIPv4SA OBJECT-TYPE
    SYNTAX         IpAddress
    MAX-ACCESS     read-write
    STATUS         current
    DESCRIPTION
        "The IPv4 Source Address value of low-acl entry."
    ::= { es2226LowAclEntry 15 }

es2226LowAclIPv4SAMask OBJECT-TYPE
    SYNTAX         IpAddress
    MAX-ACCESS     read-write
    STATUS         current
    DESCRIPTION
        "The IPv4 Source Address mask value of low-acl entry."
    ::= { es2226LowAclEntry 16 }

es2226LowAclL4DestinationPort OBJECT-TYPE
    SYNTAX         INTEGER(0..65535)
    MAX-ACCESS     read-write
    STATUS         current
    DESCRIPTION
        "The L4 destination port number of low-acl entry.
         IPv4 L4 destination port, from 0 to 65535"
    ::= { es2226LowAclEntry 17 }

es2226LowAclL4SourcePort OBJECT-TYPE
    SYNTAX         INTEGER(0..65535)
    MAX-ACCESS     read-write
    STATUS         current
    DESCRIPTION
        "The L4 source port number of low-acl entry.
         IPv4 L4 source port, from 0 to 65535"
    ::= { es2226LowAclEntry 18 }

es2226LowAclActionIBForwardDecision OBJECT-TYPE
    SYNTAX         INTEGER(0..3)
    MAX-ACCESS     read-write
    STATUS         current
    DESCRIPTION
        "The forward decision in in-Band.
         0 : No change,
         1 : Use new forward map,
         2 : ORed with new map,
         3 : Explicit actions
        "
    ::= { es2226LowAclEntry 19 }

es2226LowAclActionIBForwardMap OBJECT-TYPE
    SYNTAX         INTEGER(0..26)
    MAX-ACCESS     read-write
    STATUS         current
    DESCRIPTION
        "If es2226LowAclActionIBForwardDecision as 0 then
            0 : As ARL map.
         If es2226LowAclActionIBForwardDecision as 1 or 2 then
	    0 : All Linked-Port,
	    1~26 : Port 1 ~ Port 26
	 If  es2226LowAclActionIBForwardDecision as 3 then
	    0 : As ARL map,
	    1 : As ARL map and copy to mirror port,
	    2 : Drop,
	    3 : Forward to mirror port.
    	"
    ::= { es2226LowAclEntry 20 }

es2226LowAclActionIBModifyDSCPPacket OBJECT-TYPE
    SYNTAX         INTEGER(0|1)
    MAX-ACCESS     read-write
    STATUS         current
    DESCRIPTION
        "Modify DSCP packet value in in-Band.
         0 : Any,
         1 : Specific.
        "
    ::= { es2226LowAclEntry 21 }

es2226LowAclActionIBModifyDSCPValue OBJECT-TYPE
    SYNTAX         INTEGER(0..63)
    MAX-ACCESS     read-write
    STATUS         current
    DESCRIPTION
        "Be used by es2226LowAclActionIBModifyDSCPPacket as 1.
         New DSCP field value, from 0 to 63"
    ::= { es2226LowAclEntry 22 }

es2226LowAclActionOBForwardDecision OBJECT-TYPE
    SYNTAX         INTEGER(0..3)
    MAX-ACCESS     read-write
    STATUS         current
    DESCRIPTION
        "The forward decision in out-Band.
         0 : No change,
         1 : Use new forward map,
         2 : ORed with new map,
         3 : Explicit actions
        "
    ::= { es2226LowAclEntry 23 }

es2226LowAclActionOBForwardMap OBJECT-TYPE
    SYNTAX         INTEGER(0..26)
    MAX-ACCESS     read-write
    STATUS         current
    DESCRIPTION
        "If es2226LowAclActionOBForwardDecision as 0
            0 : As ARL map.
         If es2226LowAclActionOBForwardDecision as 1 or 2 then
	    0 : All Linked-Port,
	    1~26 : Port 1 ~ Port 26
	 If es2226LowAclActionOBForwardDecision as 3 then
	    0 : As ARL map,
	    1 : As ARL map and copy to mirror port ,
	    2 : Drop,
	    3 : Forward to mirror port.
    	"
    ::= { es2226LowAclEntry 24 }

es2226LowAclActionOBModifyDSCPPacket OBJECT-TYPE
    SYNTAX         INTEGER(0|1)
    MAX-ACCESS     read-write
    STATUS         current
    DESCRIPTION
        "Modify DSCP packet value in out-Band.
         0 : Any,
         1 : Specific.
        "
    ::= { es2226LowAclEntry 25 }

es2226LowAclActionOBModifyDSCPValue OBJECT-TYPE
    SYNTAX         INTEGER(0..63)
    MAX-ACCESS     read-write
    STATUS         current
    DESCRIPTION
        "Be used by es2226LowAclActionOBModifyDSCPPacket as 1.
         New DSCP field value, from 0 to 63"
    ::= { es2226LowAclEntry 26 }

es2226LowAclActionModifyDot1PPacket OBJECT-TYPE
    SYNTAX         INTEGER(0|1)
    MAX-ACCESS     read-write
    STATUS         current
    DESCRIPTION
        "Modify 802.1P packet value.
         0 : Any,
         1 : Specific.
        "
    ::= { es2226LowAclEntry 27 }

es2226LowAclActionModifyDot1PValue OBJECT-TYPE
    SYNTAX         INTEGER(0..7)
    MAX-ACCESS     read-write
    STATUS         current
    DESCRIPTION
        "Be used by es2226LowAclActionModifyDot1PPacket as 1.
         New 802.1p field value, from 0 to 7"
    ::= { es2226LowAclEntry 28 }

es2226LowAclActionModifyQoSPacket OBJECT-TYPE
    SYNTAX         INTEGER(0|1)
    MAX-ACCESS     read-write
    STATUS         current
    DESCRIPTION
        "Modify QoS packet value.
         0 : Any,
         1 : Specific.
        "
    ::= { es2226LowAclEntry 29 }

es2226LowAclActionModifyQoSValue OBJECT-TYPE
    SYNTAX         INTEGER(0..3)
    MAX-ACCESS     read-write
    STATUS         current
    DESCRIPTION
        "Be used by es2226LowAclActionModifyQoSPacket as 1.
         New QoS field value, from 0 to 3"
    ::= { es2226LowAclEntry 30 }

es2226LowAclRateMeter OBJECT-TYPE
    SYNTAX         INTEGER(64..1024000)
    MAX-ACCESS     read-write
    STATUS         current
    DESCRIPTION
        "The rate meter(64..1024000) of low-acl entry."
    ::= { es2226LowAclEntry 31 }

es2226LowAclRowStatus  OBJECT-TYPE
    SYNTAX      INTEGER(1..3)
    MAX-ACCESS  read-write
    STATUS      current
    DESCRIPTION
        "The row status of low-acl entry.
         1 : active,
         2 : not-inService,
         3 : delete
        "
    ::= { es2226LowAclEntry 32 }

es2226TrunkInfo       OBJECT IDENTIFIER ::= { es2226Produces 23 }

es2226TrunkPort      OBJECT IDENTIFIER ::= { es2226TrunkInfo 1 }

es2226TrunkPortTable  OBJECT-TYPE
    SYNTAX      SEQUENCE OF ES2226TrunkPortEntry
    MAX-ACCESS  not-accessible
    STATUS      current
    DESCRIPTION
        " "
    ::= { es2226TrunkPort 1 }

es2226TrunkPortEntry OBJECT-TYPE
    SYNTAX      ES2226TrunkPortEntry
    MAX-ACCESS  not-accessible
    STATUS      current
    DESCRIPTION
        "Entry(s) for trunk table."
    INDEX {es2226TrunkPortIndex}
    ::= { es2226TrunkPortTable 1 }

ES2226TrunkPortEntry ::=
SEQUENCE {
    es2226TrunkPortIndex				INTEGER,
    es2226TrunkPortMethod   				INTEGER,
    es2226TrunkPortGroup 				INTEGER,
    es2226TrunkPortActiveLacp				INTEGER,
    es2226TrunkPortAggtr				INTEGER,
    es2226TrunkPortStatus				INTEGER,
    es2226TrunkPortCurrentMode				INTEGER
}

es2226TrunkPortIndex  OBJECT-TYPE
    SYNTAX      INTEGER(1..26)
    MAX-ACCESS  not-accessible
    STATUS      current
    DESCRIPTION
        "The port index of trunk table."
    ::= { es2226TrunkPortEntry 1 }

es2226TrunkPortMethod  OBJECT-TYPE
    SYNTAX      INTEGER(0..2)
    MAX-ACCESS  read-write
    STATUS      current
    DESCRIPTION
        "The method of trunk port.
	 0 : None,
	 1 : LACP,
	 2 : Static.
        "
    ::= { es2226TrunkPortEntry 2 }

es2226TrunkPortGroup  OBJECT-TYPE
    SYNTAX      INTEGER(0..12)
    MAX-ACCESS  read-write
    STATUS      current
    DESCRIPTION
        "The group(0~12) of trunk port."
    ::= { es2226TrunkPortEntry 3 }

es2226TrunkPortActiveLacp  OBJECT-TYPE
    SYNTAX      INTEGER(0|1)
    MAX-ACCESS  read-write
    STATUS      current
    DESCRIPTION
        "The active lacp mode of trunk port.
	 0 : Passive,
	 1 : Active.
        "
    ::= { es2226TrunkPortEntry 4 }

es2226TrunkPortAggtr  OBJECT-TYPE
    SYNTAX      INTEGER(1..26)
    MAX-ACCESS  read-only
    STATUS      current
    DESCRIPTION
        "The Aggtr of trunk port."
    ::= { es2226TrunkPortEntry 5 }

es2226TrunkPortStatus  OBJECT-TYPE
    SYNTAX      INTEGER(0|1)
    MAX-ACCESS  read-only
    STATUS      current
    DESCRIPTION
        "The status of trunk port.
         0 : None,
         1 : Ready.
        "
    ::= { es2226TrunkPortEntry 6 }

es2226TrunkPortCurrentMode  OBJECT-TYPE
    SYNTAX      INTEGER(0..2)
    MAX-ACCESS  read-write
    STATUS      current
    DESCRIPTION
        "The current mode of trunk port entry.
	 0 : Active mode,
	 1 : Edit mode,
	 2 : Do edit.
        "
    ::= { es2226TrunkPortEntry 7 }

es2226AggregatorView      OBJECT IDENTIFIER ::= { es2226TrunkInfo 2 }

es2226AggregatorViewTable  OBJECT-TYPE
    SYNTAX      SEQUENCE OF ES2226AggregatorViewEntry
    MAX-ACCESS  not-accessible
    STATUS      current
    DESCRIPTION
        " "
    ::= { es2226AggregatorView 1 }

es2226AggregatorViewEntry OBJECT-TYPE
    SYNTAX      ES2226AggregatorViewEntry
    MAX-ACCESS  not-accessible
    STATUS      current
    DESCRIPTION
        "Entry(s) for aggregator view table."
    INDEX {es2226AggregatorViewIndex}
    ::= { es2226AggregatorViewTable 1 }

ES2226AggregatorViewEntry ::=
SEQUENCE {
    es2226AggregatorViewIndex				INTEGER,
    es2226AggregatorViewMethod 				INTEGER,
    es2226AggregatorViewMemberPorts 			DisplayString,
    es2226AggregatorViewReadyPorts			DisplayString
}

es2226AggregatorViewIndex  OBJECT-TYPE
    SYNTAX      INTEGER(1..26)
    MAX-ACCESS  not-accessible
    STATUS      current
    DESCRIPTION
        "The port index of aggregator view table."
    ::= { es2226AggregatorViewEntry 1 }

es2226AggregatorViewMethod  OBJECT-TYPE
    SYNTAX      INTEGER(0..2)
    MAX-ACCESS  read-only
    STATUS      current
    DESCRIPTION
        "The method of aggregator view table.
         0 : None,
	 1 : LACP,
	 2 : Static.
        "
    ::= { es2226AggregatorViewEntry 2 }

es2226AggregatorViewMemberPorts  OBJECT-TYPE
    SYNTAX      DisplayString
    MAX-ACCESS  read-only
    STATUS      current
    DESCRIPTION
        "The member ports of aggregator view table."
    ::= { es2226AggregatorViewEntry 3 }

es2226AggregatorViewReadyPorts  OBJECT-TYPE
    SYNTAX      DisplayString
    MAX-ACCESS  read-only
    STATUS      current
    DESCRIPTION
        "The ready ports of aggregator view table."
    ::= { es2226AggregatorViewEntry 4 }

es2226LacpSystemConfiguration     OBJECT IDENTIFIER ::= { es2226TrunkInfo 3 }

es2226LacpSystemPriority  OBJECT-TYPE
    SYNTAX      INTEGER(1..65535)
    MAX-ACCESS  read-write
    STATUS      current
    DESCRIPTION
        "The priority of LACP system."
    ::= { es2226LacpSystemConfiguration 1 }

es2226LacpSystemHashMethod  OBJECT-TYPE
    SYNTAX      INTEGER(0..5)
    MAX-ACCESS  read-write
    STATUS      current
    DESCRIPTION
        "The hash method of LACP system.
	 0 : DA and SA
         1 : SA
         2 : DA
         3 : IPv4 DIP
         4 : IPv4 SIP
         5 : DA, SA, IPv4 DIP and IPv4 SIP
        "
    ::= { es2226LacpSystemConfiguration 2 }

es2226Dhcprelay            OBJECT IDENTIFIER ::= { es2226Produces 25 }

es2226DhcpRelayState OBJECT-TYPE
    SYNTAX      INTEGER(0|1)
    MAX-ACCESS  read-write
    STATUS      current
    DESCRIPTION
        "Set DHCP Relay State.
         0 : Disable,
         1 : Enable.
         When DHCP or DHCP Snooping is already running. Please disable DHCP or DHCP Snooping first, and then enable DHCP Relay again.
        "
    ::= { es2226Dhcprelay 1 }

es2226DhcpRelayLifeTime OBJECT-TYPE
    SYNTAX      INTEGER(1..10)
    MAX-ACCESS  read-write
    STATUS      current
    DESCRIPTION
        "Set wait Server reply time.
         time: from 1 to 10 second(s)"
    ::= { es2226Dhcprelay 2 }

es2226DhcpRelayOption82 OBJECT-TYPE
    SYNTAX      INTEGER(0|1)
    MAX-ACCESS  read-write
    STATUS      current
    DESCRIPTION
        "Option82 state in Dhcp Relay.
         0 : Disable,
         1 : Enable.
        "
    ::= { es2226Dhcprelay 3 }

es2226DhcpRelayOption82Action OBJECT-TYPE
    SYNTAX      INTEGER(0..2)
    MAX-ACCESS  read-write
    STATUS      current
    DESCRIPTION
        "The action of the switch which is existing relay information in packets received from DHCP clients.
         0 : Replace,
         1 : Keep,
         2 : Drop."
    ::= { es2226Dhcprelay 4 }

es2226DhcpRelayServerPort OBJECT-TYPE
    SYNTAX      DisplayString
    MAX-ACCESS  read-write
    STATUS      current
    DESCRIPTION
        "The Dhcp Relay Server Port.
         Server port cannot exceed more than two ports."
    ::= { es2226Dhcprelay 5 }

es2226DhcpRelayServerIP OBJECT-TYPE
    SYNTAX      IpAddress
    MAX-ACCESS  read-write
    STATUS      current
    DESCRIPTION
        "Server ip"
    ::= { es2226Dhcprelay 6 }

es2226Multicast        OBJECT IDENTIFIER ::= { es2226Produces 26 }

es2226IgmpSetting      OBJECT IDENTIFIER ::= { es2226Multicast 1 }

es2226IgmpSnoopingState OBJECT-TYPE
    SYNTAX         INTEGER(0|1)
    MAX-ACCESS     read-write
    STATUS         current
    DESCRIPTION
        "Set IGMP Snooping State.
         0 : Disable,
         1 : Enable.
        "
    ::= { es2226IgmpSetting 1 }

es2226IgmpSnoopingUnregisterMulticastFlooding OBJECT-TYPE
    SYNTAX         INTEGER(0|1)
    MAX-ACCESS     read-write
    STATUS         current
    DESCRIPTION
        "Set Unregister Multicast Flooding State.
         0 : Disable,
         1 : Enable.
        "
    ::= { es2226IgmpSetting 2 }

es2226IgmpSnoopingGeneralQueryInterval  OBJECT-TYPE
    SYNTAX      INTEGER(1..2000)
    MAX-ACCESS  read-write
    STATUS      current
    DESCRIPTION
        "Set general query interval.
         interval: from 1 to 2000 second(s)"
    ::= { es2226IgmpSetting 3 }

es2226IgmpSnoopingGeneralQueryMaxResponseTime  OBJECT-TYPE
    SYNTAX      INTEGER(1..10)
    MAX-ACCESS  read-write
    STATUS      current
    DESCRIPTION
        "Set general query max response time.
         time: from 1 to 10 second(s)"
    ::= { es2226IgmpSetting 4 }

es2226IgmpSnoopingGeneralQueryTimeout  OBJECT-TYPE
    SYNTAX      INTEGER(1..30)
    MAX-ACCESS  read-write
    STATUS      current
    DESCRIPTION
        "Set general query timeout.
         timeout: from 1 to 30 second(s)"
    ::= { es2226IgmpSetting 5 }

es2226IgmpSnoopingSpecificQueryCount  OBJECT-TYPE
    SYNTAX      INTEGER(1..10)
    MAX-ACCESS  read-write
    STATUS      current
    DESCRIPTION
        "Set specific query count.
         count: from 1 to 10"
    ::= { es2226IgmpSetting 6 }

es2226IgmpSnoopingSpecificQueryMaxResponseTime  OBJECT-TYPE
    SYNTAX      INTEGER(1..10)
    MAX-ACCESS  read-write
    STATUS      current
    DESCRIPTION
        "Set specific query max response time.
         time: from 1 to 10 second(s)"
    ::= { es2226IgmpSetting 7 }

es2226IgmpSnoopingSpecificQueryTimeout  OBJECT-TYPE
    SYNTAX      INTEGER(1..30)
    MAX-ACCESS  read-write
    STATUS      current
    DESCRIPTION
        "Set specific query timeout.
         timeout: from 1 to 30 second(s)"
    ::= { es2226IgmpSetting 8 }

es2226IgmpSnoopingSettingTable  OBJECT-TYPE
    SYNTAX      SEQUENCE OF ES2226IgmpSnoopingSettingEntry
    MAX-ACCESS  not-accessible
    STATUS      current
    DESCRIPTION
        " "
    ::= { es2226IgmpSetting 9 }

es2226IgmpSnoopingSettingEntry OBJECT-TYPE
    SYNTAX      ES2226IgmpSnoopingSettingEntry
    MAX-ACCESS  not-accessible
    STATUS      current
    DESCRIPTION
        "Entry(s) for IGMP snooping port setting table."
    INDEX {es2226IgmpSnoopingSettingPortIndex}
    ::= { es2226IgmpSnoopingSettingTable 1 }

ES2226IgmpSnoopingSettingEntry ::=
SEQUENCE {
    es2226IgmpSnoopingSettingPortIndex		INTEGER,
    es2226IgmpSnoopingSettingMulticastGroupLimit		INTEGER,
    es2226IgmpSnoopingSettingIGMPRouter		INTEGER
}

es2226IgmpSnoopingSettingPortIndex  OBJECT-TYPE
    SYNTAX      INTEGER(1..26)
    MAX-ACCESS  not-accessible
    STATUS      current
    DESCRIPTION
        "The port index of IGMP snooping port setting table."
    ::= { es2226IgmpSnoopingSettingEntry 1 }

es2226IgmpSnoopingSettingMulticastGroupLimit OBJECT-TYPE
    SYNTAX         INTEGER(0..256)
    MAX-ACCESS     read-write
    STATUS         current
    DESCRIPTION
        "Set multicast group limit. Limit range from 0 to 256."
    ::= { es2226IgmpSnoopingSettingEntry 2 }

es2226IgmpSnoopingSettingIGMPRouter OBJECT-TYPE
    SYNTAX         INTEGER(0|1)
    MAX-ACCESS     read-write
    STATUS         current
    DESCRIPTION
        "Set IGMP router.
         0 : non-router,
         1 : router.
        "
    ::= { es2226IgmpSnoopingSettingEntry 3 }

es2226IgmpVlan      OBJECT IDENTIFIER ::= { es2226Multicast 2 }

es2226IgmpVlanNumbers  OBJECT-TYPE
    SYNTAX      INTEGER(1..256)
    MAX-ACCESS  read-only
    STATUS      current
    DESCRIPTION
        "Total numbers for igmp vlan."
    ::= { es2226IgmpVlan 1 }

es2226IgmpVlanCreatStatus OBJECT-TYPE
    SYNTAX         INTEGER(0..4094)
    MAX-ACCESS     read-write
    STATUS         current
    DESCRIPTION
        "Create IGMP Vlan Vid.
         Vid: from 1 to 4094"
    ::= { es2226IgmpVlan 2 }

es2226IgmpVlanTable  OBJECT-TYPE
    SYNTAX      SEQUENCE OF ES2226IgmpVlanEntry
    MAX-ACCESS  not-accessible
    STATUS      current
    DESCRIPTION
        " "
    ::= { es2226IgmpVlan 3 }

es2226IgmpVlanEntry OBJECT-TYPE
    SYNTAX      ES2226IgmpVlanEntry
    MAX-ACCESS  not-accessible
    STATUS      current
    DESCRIPTION
        "Entry(s) for Igmp Vlan table."
    INDEX {es2226IgmpVlanIndex}
    ::= { es2226IgmpVlanTable 1 }

ES2226IgmpVlanEntry ::=
SEQUENCE {
    es2226IgmpVlanIndex						INTEGER,
    es2226IgmpVlanVid					    INTEGER,
    es2226IgmpVlanRowStatus					INTEGER
}

es2226IgmpVlanIndex  OBJECT-TYPE
    SYNTAX      INTEGER(1..64)
    MAX-ACCESS  not-accessible
    STATUS      current
    DESCRIPTION
        "The entry index of Igmp Vlan table."
    ::= { es2226IgmpVlanEntry 1 }

es2226IgmpVlanVid OBJECT-TYPE
    SYNTAX         INTEGER(1..4094)
    MAX-ACCESS     read-only
    STATUS         current
    DESCRIPTION
        "The vid of igmp vlan entry."
    ::= { es2226IgmpVlanEntry 2 }

es2226IgmpVlanRowStatus  OBJECT-TYPE
    SYNTAX      INTEGER(1..3)
    MAX-ACCESS  read-write
    STATUS      current
    DESCRIPTION
        "The row status of igmp vlan entry.
         1 : active,
         2 : not-inService,
         3 : delete
        "
    ::= { es2226IgmpVlanEntry 3 }

es2226IgmpVlanGroupAllow      OBJECT IDENTIFIER ::= { es2226Multicast 3 }

es2226IgmpVlanGroupAllowCreatStatus OBJECT-TYPE
    SYNTAX         INTEGER(0..4094)
    MAX-ACCESS     read-write
    STATUS         current
    DESCRIPTION
        "Create IGMP Group Allow Entry."
    ::= { es2226IgmpVlanGroupAllow 1 }

es2226IgmpVlanGroupAllowTable  OBJECT-TYPE
    SYNTAX      SEQUENCE OF ES2226IgmpVlanGroupAllowEntry
    MAX-ACCESS  not-accessible
    STATUS      current
    DESCRIPTION
        " "
    ::= { es2226IgmpVlanGroupAllow 2 }

es2226IgmpVlanGroupAllowEntry OBJECT-TYPE
    SYNTAX      ES2226IgmpVlanGroupAllowEntry
    MAX-ACCESS  not-accessible
    STATUS      current
    DESCRIPTION
        "Entry(s) for Igmp Group Allow table."
    INDEX {es2226IgmpVlanGroupAllowIndex}
    ::= { es2226IgmpVlanGroupAllowTable 1 }

ES2226IgmpVlanGroupAllowEntry ::=
SEQUENCE {
    es2226IgmpVlanGroupAllowIndex				    INTEGER,
    es2226IgmpVlanGroupAllowStartAddress			IpAddress,
    es2226IgmpVlanGroupAllowEndAddress				IpAddress,
    es2226IgmpVlanGroupAllowVid				        INTEGER,
    es2226IgmpVlanGroupAllowPortMember				DisplayString,
    es2226IgmpVlanGroupAllowRowStatus				INTEGER
}

es2226IgmpVlanGroupAllowIndex  OBJECT-TYPE
    SYNTAX      INTEGER(1..256)
    MAX-ACCESS  not-accessible
    STATUS      current
    DESCRIPTION
        "The entry index of Igmp Group Allow table."
    ::= { es2226IgmpVlanGroupAllowEntry 1 }

es2226IgmpVlanGroupAllowStartAddress OBJECT-TYPE
    SYNTAX      IpAddress
    MAX-ACCESS  read-write
    STATUS      current
    DESCRIPTION
        "Start address of Group Allow entry."
    ::= { es2226IgmpVlanGroupAllowEntry 2 }

es2226IgmpVlanGroupAllowEndAddress OBJECT-TYPE
    SYNTAX      IpAddress
    MAX-ACCESS  read-write
    STATUS      current
    DESCRIPTION
        "End address of Group Allow entry."
    ::= { es2226IgmpVlanGroupAllowEntry 3 }

es2226IgmpVlanGroupAllowVid  OBJECT-TYPE
    SYNTAX      INTEGER(0..4094)
    MAX-ACCESS  read-write
    STATUS      current
    DESCRIPTION
        "VLAN ID of Group Allow entry."
    ::= { es2226IgmpVlanGroupAllowEntry 4 }

es2226IgmpVlanGroupAllowPortMember  OBJECT-TYPE
    SYNTAX      DisplayString
    MAX-ACCESS  read-write
    STATUS      current
    DESCRIPTION
        "Port Member of Group Allow entry."
    ::= { es2226IgmpVlanGroupAllowEntry 5 }

es2226IgmpVlanGroupAllowRowStatus  OBJECT-TYPE
    SYNTAX      INTEGER(1..3)
    MAX-ACCESS  read-write
    STATUS      current
    DESCRIPTION
        "The row status of igmp group allow entry.
         1 : active,
         2 : not-inService,
         3 : delete
        "
    ::= { es2226IgmpVlanGroupAllowEntry 6 }

es2226MvrSetting      OBJECT IDENTIFIER ::= { es2226Multicast 4 }

es2226MvrSettingMulticastVlanRegistration OBJECT-TYPE
    SYNTAX         INTEGER(0|1)
    MAX-ACCESS     read-write
    STATUS         current
    DESCRIPTION
        "Set MVR State.
         0 : Disable,
         1 : Enable.
        "
    ::= { es2226MvrSetting 1 }

es2226MvrSettingMulticastVlanIdConf  OBJECT-TYPE
    SYNTAX      INTEGER(2..4094)
    MAX-ACCESS  read-write
    STATUS      current
    DESCRIPTION
        "Get/Set multicast vlan vid. This value whill be kept in buffer.
        Will be activity after enable Multicast Vlan Registration.
         vid: from 2 to 4094, 1: reserved for default vlan"
    ::= { es2226MvrSetting 2 }

es2226MvrSettingMulticastVlanIdShow  OBJECT-TYPE
    SYNTAX      INTEGER(0..4094)
    MAX-ACCESS  read-only
    STATUS      current
    DESCRIPTION
        "Get the multicast vlan vid real value.
         vid: from 2 to 4094"
    ::= { es2226MvrSetting 3 }

es2226MvrSettingTable  OBJECT-TYPE
    SYNTAX      SEQUENCE OF ES2226MvrSettingEntry
    MAX-ACCESS  not-accessible
    STATUS      current
    DESCRIPTION
        " "
    ::= { es2226MvrSetting 4 }

es2226MvrSettingEntry OBJECT-TYPE
    SYNTAX      ES2226MvrSettingEntry
    MAX-ACCESS  not-accessible
    STATUS      current
    DESCRIPTION
        "Entry(s) for MVR port setting table."
    INDEX {es2226MvrSettingPort}
    ::= { es2226MvrSettingTable 1 }

ES2226MvrSettingEntry ::=
SEQUENCE {
    es2226MvrSettingPort		    INTEGER,
    es2226MvrSettingServerType		INTEGER,
    es2226MvrSettingTagging		    INTEGER
}

es2226MvrSettingPort  OBJECT-TYPE
    SYNTAX      INTEGER(1..26)
    MAX-ACCESS  not-accessible
    STATUS      current
    DESCRIPTION
        "The port index of MVR port setting table."
    ::= { es2226MvrSettingEntry 1 }

es2226MvrSettingServerType OBJECT-TYPE
    SYNTAX         INTEGER(0..2)
    MAX-ACCESS     read-write
    STATUS         current
    DESCRIPTION
        "Set mvr service type.
         type: 0(None), 1(Client), 2(Router).At least one clent or router port."
    ::= { es2226MvrSettingEntry 2 }

es2226MvrSettingTagging OBJECT-TYPE
    SYNTAX         INTEGER(0|1)
    MAX-ACCESS     read-write
    STATUS         current
    DESCRIPTION
        "Set mvr tagging.
         0 : untag-out,
         1 : tag-out.
        "
    ::= { es2226MvrSettingEntry 3 }

es2226MulticastStatus      OBJECT IDENTIFIER ::= { es2226Multicast 5 }

es2226MulticastStatusTable  OBJECT-TYPE
    SYNTAX      SEQUENCE OF ES2226MulticastStatusEntry
    MAX-ACCESS  not-accessible
    STATUS      current
    DESCRIPTION
        " "
    ::= { es2226MulticastStatus 1 }

es2226MulticastStatusEntry OBJECT-TYPE
    SYNTAX      ES2226MulticastStatusEntry
    MAX-ACCESS  not-accessible
    STATUS      current
    DESCRIPTION
        "Entry(s) for Multicast Status table."
    INDEX {es2226MulticastStatusIndex}
    ::= { es2226MulticastStatusTable 1 }

ES2226MulticastStatusEntry ::=
SEQUENCE {
    es2226MulticastStatusIndex				INTEGER,
    es2226MulticastStatusVid   				INTEGER,
    es2226MulticastStatusMulticastGroup 				IpAddress,
    es2226MulticastStatusPortMember				DisplayString
}

es2226MulticastStatusIndex  OBJECT-TYPE
    SYNTAX      INTEGER(1..256)
    MAX-ACCESS  not-accessible
    STATUS      current
    DESCRIPTION
        "The port index of trunk table."
    ::= { es2226MulticastStatusEntry 1 }

es2226MulticastStatusVid OBJECT-TYPE
    SYNTAX         INTEGER(1..4094)
    MAX-ACCESS     read-only
    STATUS         current
    DESCRIPTION
        "The Vid of multicast status table."
    ::= { es2226MulticastStatusEntry 2 }

es2226MulticastStatusMulticastGroup OBJECT-TYPE
    SYNTAX      IpAddress
    MAX-ACCESS  read-only
    STATUS      current
    DESCRIPTION
        "The Multicast Group of multicast status table."
    ::= { es2226MulticastStatusEntry 3 }

es2226MulticastStatusPortMember  OBJECT-TYPE
    SYNTAX      DisplayString
    MAX-ACCESS  read-only
    STATUS      current
    DESCRIPTION
        "The Port Member of multicast status table."
    ::= { es2226MulticastStatusEntry 4 }

es2226RadiusIgmpSetting      OBJECT IDENTIFIER ::= { es2226Multicast 6 }

es2226RadiusIgmpServer1 OBJECT-TYPE
    SYNTAX      IpAddress
    MAX-ACCESS  read-write
    STATUS      current
    DESCRIPTION
        "Radius Igmp Server1"
    ::= { es2226RadiusIgmpSetting 1 }

es2226RadiusIgmpPortNumber1 OBJECT-TYPE
    SYNTAX      INTEGER(1..65535)
    MAX-ACCESS  read-write
    STATUS      current
    DESCRIPTION
        "Set Radius Igmp port number1.
         port number: from 1 to 65535"
    ::= { es2226RadiusIgmpSetting 2 }

es2226RadiusIgmpServer2 OBJECT-TYPE
    SYNTAX      IpAddress
    MAX-ACCESS  read-write
    STATUS      current
    DESCRIPTION
        "Radius Igmp Server2"
    ::= { es2226RadiusIgmpSetting 3 }

es2226RadiusIgmpPortNumber2 OBJECT-TYPE
    SYNTAX      INTEGER(1..65535)
    MAX-ACCESS  read-write
    STATUS      current
    DESCRIPTION
        "Set Radius Igmp port number2.
         port number: from 1 to 65535"
    ::= { es2226RadiusIgmpSetting 4 }

es2226RadiusIgmpSecretKey1  OBJECT-TYPE
    SYNTAX         DisplayString
    MAX-ACCESS     read-write
    STATUS         current
    DESCRIPTION
        "Set Radius Igmp secret key1"
    ::= { es2226RadiusIgmpSetting 5 }

es2226RadiusIgmpAccountingServer1 OBJECT-TYPE
    SYNTAX      IpAddress
    MAX-ACCESS  read-write
    STATUS      current
    DESCRIPTION
        "Radius Igmp Accounting Server1"
    ::= { es2226RadiusIgmpSetting 6 }

es2226RadiusIgmpAccountingPortNumber1 OBJECT-TYPE
    SYNTAX      INTEGER(1..65535)
    MAX-ACCESS  read-write
    STATUS      current
    DESCRIPTION
        "Set Radius Igmp Accounting port number1.
         port number: from 1 to 65535"
    ::= { es2226RadiusIgmpSetting 7 }

es2226RadiusIgmpAccountingServer2 OBJECT-TYPE
    SYNTAX      IpAddress
    MAX-ACCESS  read-write
    STATUS      current
    DESCRIPTION
        "Radius Igmp Accounting Server2"
    ::= { es2226RadiusIgmpSetting 8 }

es2226RadiusIgmpAccountingPortNumber2 OBJECT-TYPE
    SYNTAX      INTEGER(1..65535)
    MAX-ACCESS  read-write
    STATUS      current
    DESCRIPTION
        "Set Radius Igmp Accounting port number2.
         port number: from 1 to 65535"
    ::= { es2226RadiusIgmpSetting 9 }

es2226RadiusIgmpSecretKey2  OBJECT-TYPE
    SYNTAX         DisplayString
    MAX-ACCESS     read-write
    STATUS         current
    DESCRIPTION
        "Set Radius Igmp secret key2"
    ::= { es2226RadiusIgmpSetting 10 }

es2226RadiusIgmpResponseTimeout OBJECT-TYPE
    SYNTAX      INTEGER(2..60)
    MAX-ACCESS  read-write
    STATUS      current
    DESCRIPTION
        "Set radius-igmp timeout.
         time: 2 ~ 60 seconds"
    ::= { es2226RadiusIgmpSetting 11 }

es2226RadiusIgmpNumberOfRetry OBJECT-TYPE
    SYNTAX      INTEGER(0..10)
    MAX-ACCESS  read-write
    STATUS      current
    DESCRIPTION
        "Set radius-igmp number of retry.
         value: 0 ~ 10 times"
    ::= { es2226RadiusIgmpSetting 12 }

es2226RadiusIgmpPortMember  OBJECT-TYPE
    SYNTAX      DisplayString
    MAX-ACCESS  read-write
    STATUS      current
    DESCRIPTION
        "The Port Member of  Radius Igmp. 0: no port member"
    ::= { es2226RadiusIgmpSetting 13 }

END
