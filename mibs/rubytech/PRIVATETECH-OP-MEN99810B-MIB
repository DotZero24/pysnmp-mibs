PRIVATETECH-OP-MEN99810B-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

privatetech MODULE-IDENTITY
        LAST-UPDATED "201608240000Z"
        ORGANIZATION "Corp."
        CONTACT-INFO
            ""
        DESCRIPTION
            ""
        ::= { enterprises 5205 }

switch                                                          OBJECT IDENTIFIER ::= { privatetech 2 }

opmen99810bProductId                                             OBJECT IDENTIFIER ::= { switch 94 }

opmen99810bSystem                                                OBJECT IDENTIFIER ::= { opmen99810bProductId 1 }

opmen99810bSystemInformation                                     OBJECT IDENTIFIER ::= { opmen99810bSystem 1 }

opmen99810bModelName OBJECT-TYPE
   SYNTAX       DisplayString
   MAX-ACCESS   read-only
   STATUS       current
   DESCRIPTION
       ""
 ::= { opmen99810bSystemInformation 1 }

opmen99810bBIOSVersion OBJECT-TYPE
   SYNTAX       DisplayString
   MAX-ACCESS   read-only
   STATUS       current
   DESCRIPTION
       ""
   ::= { opmen99810bSystemInformation 2 }

opmen99810bFirmwareVersion OBJECT-TYPE
   SYNTAX       DisplayString
   MAX-ACCESS   read-only
   STATUS       current
   DESCRIPTION
       ""
   ::= { opmen99810bSystemInformation 3 }

opmen99810bHardwareMechanicalVersion OBJECT-TYPE
   SYNTAX       DisplayString
   MAX-ACCESS   read-only
   STATUS       current
   DESCRIPTION
       ""
   ::= { opmen99810bSystemInformation 4 }

opmen99810bSerialNumber OBJECT-TYPE
   SYNTAX       DisplayString
   MAX-ACCESS   read-only
   STATUS       current
   DESCRIPTION
       ""
   ::= { opmen99810bSystemInformation 5 }

opmen99810bHostMACAddress OBJECT-TYPE
   SYNTAX       MacAddress
   MAX-ACCESS   read-only
   STATUS       current
   DESCRIPTION
       ""
   ::= { opmen99810bSystemInformation 6 }

opmen99810bConsoleBaudrate OBJECT-TYPE
   SYNTAX       DisplayString
   MAX-ACCESS   read-only
   STATUS       current
   DESCRIPTION
       ""
   ::= { opmen99810bSystemInformation 7 }

opmen99810bRAMSize OBJECT-TYPE
   SYNTAX       DisplayString
   MAX-ACCESS   read-only
   STATUS       current
   DESCRIPTION
       ""
   ::= { opmen99810bSystemInformation 8 }

opmen99810bFlashSize OBJECT-TYPE
   SYNTAX       DisplayString
   MAX-ACCESS   read-only
   STATUS       current
   DESCRIPTION
       ""
   ::= { opmen99810bSystemInformation 9 }

opmen99810bBridgeFBDSize OBJECT-TYPE
   SYNTAX       DisplayString
   MAX-ACCESS   read-only
   STATUS       current
   DESCRIPTION
       ""
   ::= { opmen99810bSystemInformation 10 }

opmen99810bTransmitQueue OBJECT-TYPE
   SYNTAX       DisplayString
   MAX-ACCESS   read-only
   STATUS       current
   DESCRIPTION
       ""
   ::= { opmen99810bSystemInformation 11 }

opmen99810bMaximumFrameSize OBJECT-TYPE
   SYNTAX       DisplayString
   MAX-ACCESS   read-only
   STATUS       current
   DESCRIPTION
       ""
   ::= { opmen99810bSystemInformation 12 }

opmen99810bCPULoad OBJECT-TYPE
   SYNTAX       DisplayString
   MAX-ACCESS   read-only
   STATUS       current
   DESCRIPTION
       ""
   ::= { opmen99810bSystemInformation 13 }

opmen99810bPowerSource OBJECT-TYPE
   SYNTAX       DisplayString
   MAX-ACCESS   read-only
   STATUS       current
   DESCRIPTION
       "Power Source"
   ::= { opmen99810bSystemInformation 14 }

opmen99810bSystemTime                                            OBJECT IDENTIFIER ::= { opmen99810bSystem 2 }

opmen99810bSystemTimeManual                                      OBJECT IDENTIFIER ::= { opmen99810bSystemTime 1 }

opmen99810bSystemTimeManualClockSource OBJECT-TYPE
   SYNTAX	INTEGER {useLocal(0),useNTP(1)}
   MAX-ACCESS   read-write
   STATUS       current
   DESCRIPTION
       "default: 0,
        0 : Use Local Settings,
        1 : Use NTP Server."
   ::= { opmen99810bSystemTimeManual 1 }

opmen99810bSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { opmen99810bSystemTimeManual 2 }

opmen99810bSystemTimeManualTimeZoneOffset OBJECT-TYPE
   SYNTAX       INTEGER(-720..780)
   MAX-ACCESS   read-write
   STATUS       current
   DESCRIPTION
       "Get/Set the NTP Time Zone.
        The value range is between -720 and 780 (minutes)."
   ::= { opmen99810bSystemTimeManual 3 }

opmen99810bSystemTimeManualDaylightSavings OBJECT-TYPE
   SYNTAX       INTEGER { disable(0), enable(1) }
   MAX-ACCESS   read-write
   STATUS       current
   DESCRIPTION
       "default: 0,
        0 : Disable,
        1 : Enable."
   ::= { opmen99810bSystemTimeManual 4 }

opmen99810bSystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { opmen99810bSystemTimeManual 5 }

opmen99810bSystemTimeManualDaylightSavingsType OBJECT-TYPE
   SYNTAX       INTEGER { byDates(0), recurring(1) }
   MAX-ACCESS   read-write
   STATUS       current
   DESCRIPTION
       "default: 0,
        0 : By dates,
        1 : Recurring."
   ::= { opmen99810bSystemTimeManual 6 }

opmen99810bSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { opmen99810bSystemTimeManual 7 }

opmen99810bSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { opmen99810bSystemTimeManual 8 }

opmen99810bSystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { opmen99810bSystemTimeManual 9 }

opmen99810bSystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { opmen99810bSystemTimeManual 10 }

opmen99810bSystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { opmen99810bSystemTimeManual 11 }

opmen99810bSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { opmen99810bSystemTimeManual 12 }

opmen99810bSystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { opmen99810bSystemTimeManual 13 }

opmen99810bSystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { opmen99810bSystemTimeManual 14 }

opmen99810bSystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { opmen99810bSystemTimeManual 15 }

opmen99810bSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { opmen99810bSystemTimeManual 16 }

opmen99810bSystemTimeNTP                                     OBJECT IDENTIFIER ::= { opmen99810bSystemTime 2 }

opmen99810bSystemTimeNTPTable OBJECT-TYPE
   SYNTAX      SEQUENCE OF Opmen99810bSystemTimeNTPEntry
   MAX-ACCESS  not-accessible
   STATUS      current
   DESCRIPTION
       " "
   ::= { opmen99810bSystemTimeNTP 1 }

opmen99810bSystemTimeNTPEntry OBJECT-TYPE
   SYNTAX      Opmen99810bSystemTimeNTPEntry
   MAX-ACCESS  not-accessible
   STATUS      current
   DESCRIPTION
       ""
   INDEX    { opmen99810bSystemTimeNTPIndex  }
   ::= { opmen99810bSystemTimeNTPTable 1 }

Opmen99810bSystemTimeNTPEntry ::= SEQUENCE {
   opmen99810bSystemTimeNTPIndex             Integer32,
   opmen99810bSystemTimeNTPServerIPType      INTEGER,
   opmen99810bSystemTimeNTPServer            DisplayString,
   opmen99810bSystemTimeNTPCurrentMode       INTEGER
}

opmen99810bSystemTimeNTPIndex OBJECT-TYPE
   SYNTAX      Integer32(1..5)
   MAX-ACCESS  not-accessible
   STATUS      current
   DESCRIPTION
       " The index of the ntp entry. "
   ::= { opmen99810bSystemTimeNTPEntry 1 }

opmen99810bSystemTimeNTPServerIPType OBJECT-TYPE
   SYNTAX       INTEGER { ipv4(0), ipv6(1) }
   MAX-ACCESS   read-write
   STATUS       current
   DESCRIPTION
       "Default: 0,
        0 : IPv4,
        1 : IPv6."
   ::= { opmen99810bSystemTimeNTPEntry 2 }

opmen99810bSystemTimeNTPServer OBJECT-TYPE
   SYNTAX       DisplayString
   MAX-ACCESS   read-write
   STATUS       current
   DESCRIPTION
       "Get/Set the NTP Time Server1. You can use the IP address or domain name."
   ::= { opmen99810bSystemTimeNTPEntry 3 }

opmen99810bSystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { opmen99810bSystemTimeNTPEntry 4 }


opmen99810bSystemAccount                                         OBJECT IDENTIFIER ::= { opmen99810bSystem 3 }

opmen99810bSystemAccountUsers                                    OBJECT IDENTIFIER ::= { opmen99810bSystemAccount 1 }

opmen99810bSystemAccountUserCreate OBJECT-TYPE
   SYNTAX       INTEGER { none(0), create(1) }
   MAX-ACCESS   read-write
   STATUS       current
   DESCRIPTION
       "default: 0
        0 : None  (read only)
        1 : Create a user account"
   ::= { opmen99810bSystemAccountUsers 1 }

opmen99810bSystemAccountUsersTable OBJECT-TYPE
   SYNTAX      SEQUENCE OF Opmen99810bSystemAccountUsersEntry
   MAX-ACCESS  not-accessible
   STATUS      current
   DESCRIPTION
       " "
   ::= { opmen99810bSystemAccountUsers 2 }

opmen99810bSystemAccountUsersEntry OBJECT-TYPE
   SYNTAX      Opmen99810bSystemAccountUsersEntry
   MAX-ACCESS  not-accessible
   STATUS      current
   DESCRIPTION
       ""
   INDEX    { opmen99810bUserIndex  }
   ::= { opmen99810bSystemAccountUsersTable 1 }


Opmen99810bSystemAccountUsersEntry ::= SEQUENCE {
   opmen99810bUserIndex              Integer32 ,
   opmen99810bUserName               DisplayString,
   opmen99810bPassword               DisplayString,
   opmen99810bUserPrivilegeLevel     Integer32 ,
   opmen99810bAccountUserRowStatus   INTEGER
}


opmen99810bUserIndex OBJECT-TYPE
   SYNTAX      Integer32 (1..20)
   MAX-ACCESS  not-accessible
   STATUS      current
   DESCRIPTION
       " "
   ::= { opmen99810bSystemAccountUsersEntry 1 }

opmen99810bUserName OBJECT-TYPE
   SYNTAX      DisplayString (SIZE (1..32))
   MAX-ACCESS  read-write
   STATUS      current
   DESCRIPTION
       "Please use a combination of letters, numbers and underscores"
   ::= { opmen99810bSystemAccountUsersEntry 2 }

opmen99810bPassword OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { opmen99810bSystemAccountUsersEntry 3 }

opmen99810bUserPrivilegeLevel OBJECT-TYPE
   SYNTAX      Integer32 (1..15)
   MAX-ACCESS  read-write
   STATUS      current
   DESCRIPTION
       "default:1
        User privilege level range : 1 - 15"
   ::= { opmen99810bSystemAccountUsersEntry 4 }

opmen99810bAccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { opmen99810bSystemAccountUsersEntry 5 }

opmen99810bSystemAccountPrivilegeLevel                           OBJECT IDENTIFIER ::= { opmen99810bSystemAccount 2 }

opmen99810bAccountPrivilegeLevel OBJECT-TYPE
   SYNTAX      Integer32 (1..15)
   MAX-ACCESS  read-write
   STATUS      current
   DESCRIPTION
       "Default:10, Range : 1-15. "
   ::= { opmen99810bSystemAccountPrivilegeLevel 1 }

opmen99810bAggregationPrivilegeLevel OBJECT-TYPE
   SYNTAX      Integer32 (1..15)
   MAX-ACCESS  read-write
   STATUS      current
   DESCRIPTION
       "Default:10, Range : 1-15. "
   ::= { opmen99810bSystemAccountPrivilegeLevel 2 }

opmen99810bDiagnosticsPrivilegeLevel OBJECT-TYPE
   SYNTAX      Integer32 (1..15)
   MAX-ACCESS  read-write
   STATUS      current
   DESCRIPTION
       "Default:10, Range : 1-15. "
   ::= { opmen99810bSystemAccountPrivilegeLevel 3 }

opmen99810bEEEPrivilegeLevel OBJECT-TYPE
   SYNTAX      Integer32 (1..15)
   MAX-ACCESS  read-write
   STATUS      current
   DESCRIPTION
       "Default:10, Range : 1-15. "
   ::= { opmen99810bSystemAccountPrivilegeLevel 4 }

opmen99810bEasyportPrivilegeLevel OBJECT-TYPE
   SYNTAX      Integer32 (1..15)
   MAX-ACCESS  read-write
   STATUS      current
   DESCRIPTION
       "Default:10, Range : 1-15. "
   ::= { opmen99810bSystemAccountPrivilegeLevel 9 }

opmen99810bGARPPrivilegeLevel OBJECT-TYPE
   SYNTAX      Integer32 (1..15)
   MAX-ACCESS  read-write
   STATUS      current
   DESCRIPTION
       "Default:10, Range : 1-15. "
   ::= { opmen99810bSystemAccountPrivilegeLevel 10 }

opmen99810bGVRPPrivilegeLevel OBJECT-TYPE
   SYNTAX      Integer32 (1..15)
   MAX-ACCESS  read-write
   STATUS      current
   DESCRIPTION
       "Default:10, Range : 1-15. "
   ::= { opmen99810bSystemAccountPrivilegeLevel 11 }

opmen99810bIPPrivilegeLevel OBJECT-TYPE
   SYNTAX      Integer32 (1..15)
   MAX-ACCESS  read-write
   STATUS      current
   DESCRIPTION
       "Default:10, Range : 1-15. "
   ::= { opmen99810bSystemAccountPrivilegeLevel 12 }

opmen99810bIPMCSnoopingPrivilegeLevel OBJECT-TYPE
   SYNTAX      Integer32 (1..15)
   MAX-ACCESS  read-write
   STATUS      current
   DESCRIPTION
       "Default:10, Range : 1-15. "
   ::= { opmen99810bSystemAccountPrivilegeLevel 13 }

opmen99810bLACPPrivilegeLevel OBJECT-TYPE
   SYNTAX      Integer32 (1..15)
   MAX-ACCESS  read-write
   STATUS      current
   DESCRIPTION
       "Default:10, Range : 1-15. "
   ::= { opmen99810bSystemAccountPrivilegeLevel 14 }

opmen99810bLLDPPrivilegeLevel OBJECT-TYPE
   SYNTAX      Integer32 (1..15)
   MAX-ACCESS  read-write
   STATUS      current
   DESCRIPTION
       "Default:10, Range : 1-15. "
   ::= { opmen99810bSystemAccountPrivilegeLevel 15 }

opmen99810bLLDPMEDPrivilegeLevel OBJECT-TYPE
   SYNTAX      Integer32 (1..15)
   MAX-ACCESS  read-write
   STATUS      current
   DESCRIPTION
       "Default:10, Range : 1-15. "
   ::= { opmen99810bSystemAccountPrivilegeLevel 16 }

opmen99810bLoopProtectPrivilegeLevel OBJECT-TYPE
   SYNTAX      Integer32 (1..15)
   MAX-ACCESS  read-write
   STATUS      current
   DESCRIPTION
       "Default:10, Range : 1-15. "
   ::= { opmen99810bSystemAccountPrivilegeLevel 17 }

opmen99810bMACTablePrivilegeLevel OBJECT-TYPE
   SYNTAX      Integer32 (1..15)
   MAX-ACCESS  read-write
   STATUS      current
   DESCRIPTION
       "Default:10, Range : 1-15. "
   ::= { opmen99810bSystemAccountPrivilegeLevel 18 }

opmen99810bMVRPrivilegeLevel OBJECT-TYPE
   SYNTAX      Integer32 (1..15)
   MAX-ACCESS  read-write
   STATUS      current
   DESCRIPTION
       "Default:10, Range : 1-15. "
   ::= { opmen99810bSystemAccountPrivilegeLevel 22 }

opmen99810bMaintenancePrivilegeLevel OBJECT-TYPE
   SYNTAX      Integer32 (1..15)
   MAX-ACCESS  read-write
   STATUS      current
   DESCRIPTION
       "Default:10, Range : 1-15. "
   ::= { opmen99810bSystemAccountPrivilegeLevel 24 }

opmen99810bMirroringPrivilegeLevel OBJECT-TYPE
   SYNTAX      Integer32 (1..15)
   MAX-ACCESS  read-write
   STATUS      current
   DESCRIPTION
       "Default:10, Range : 1-15. "
   ::= { opmen99810bSystemAccountPrivilegeLevel 25 }

opmen99810bPortsPrivilegeLevel OBJECT-TYPE
   SYNTAX      Integer32 (1..15)
   MAX-ACCESS  read-write
   STATUS      current
   DESCRIPTION
       "Default:10, Range : 1-15. "
   ::= { opmen99810bSystemAccountPrivilegeLevel 27 }

opmen99810bPrivateVLANsPrivilegeLevel OBJECT-TYPE
   SYNTAX      Integer32 (1..15)
   MAX-ACCESS  read-write
   STATUS      current
   DESCRIPTION
       "Default:10, Range : 1-15. "
   ::= { opmen99810bSystemAccountPrivilegeLevel 28 }

opmen99810bQoSPrivilegeLevel OBJECT-TYPE
   SYNTAX      Integer32 (1..15)
   MAX-ACCESS  read-write
   STATUS      current
   DESCRIPTION
       "Default:10, Range : 1-15. "
   ::= { opmen99810bSystemAccountPrivilegeLevel 29 }

opmen99810bSFlowPrivilegeLevel OBJECT-TYPE
   SYNTAX      Integer32 (1..15)
   MAX-ACCESS  read-write
   STATUS      current
   DESCRIPTION
       "Default:10, Range : 1-15. "
   ::= { opmen99810bSystemAccountPrivilegeLevel 30 }

opmen99810bSMTPPrivilegeLevel OBJECT-TYPE
   SYNTAX      Integer32 (1..15)
   MAX-ACCESS  read-write
   STATUS      current
   DESCRIPTION
       "Default:10, Range : 1-15. "
   ::= { opmen99810bSystemAccountPrivilegeLevel 31 }

opmen99810bSNMPPrivilegeLevel OBJECT-TYPE
   SYNTAX      Integer32 (1..15)
   MAX-ACCESS  read-write
   STATUS      current
   DESCRIPTION
       "Default:10, Range : 1-15. "
   ::= { opmen99810bSystemAccountPrivilegeLevel 32 }

opmen99810bSecurityPrivilegeLevel OBJECT-TYPE
   SYNTAX      Integer32 (1..15)
   MAX-ACCESS  read-write
   STATUS      current
   DESCRIPTION
       "Default:10, Range : 1-15. "
   ::= { opmen99810bSystemAccountPrivilegeLevel 33 }

opmen99810bSingleIPPrivilegeLevel OBJECT-TYPE
   SYNTAX      Integer32 (1..15)
   MAX-ACCESS  read-write
   STATUS      current
   DESCRIPTION
       "Default:10, Range : 1-15. "
   ::= { opmen99810bSystemAccountPrivilegeLevel 34 }

opmen99810bSpanningTreePrivilegeLevel OBJECT-TYPE
   SYNTAX      Integer32 (1..15)
   MAX-ACCESS  read-write
   STATUS      current
   DESCRIPTION
       "Default:10, Range : 1-15. "
   ::= { opmen99810bSystemAccountPrivilegeLevel 35 }

opmen99810bSystemPrivilegeLevel OBJECT-TYPE
   SYNTAX      Integer32 (1..15)
   MAX-ACCESS  read-write
   STATUS      current
   DESCRIPTION
       "Default:10, Range : 1-15. "
   ::= { opmen99810bSystemAccountPrivilegeLevel 36 }

opmen99810bTrapEventPrivilegeLevel OBJECT-TYPE
   SYNTAX      Integer32 (1..15)
   MAX-ACCESS  read-write
   STATUS      current
   DESCRIPTION
       "Default:10, Range : 1-15. "
   ::= { opmen99810bSystemAccountPrivilegeLevel 37 }

opmen99810bUPnPPrivilegeLevel OBJECT-TYPE
   SYNTAX      Integer32 (1..15)
   MAX-ACCESS  read-write
   STATUS      current
   DESCRIPTION
       "Default:10, Range : 1-15. "
   ::= { opmen99810bSystemAccountPrivilegeLevel 38 }

opmen99810bVCLPrivilegeLevel OBJECT-TYPE
   SYNTAX      Integer32 (1..15)
   MAX-ACCESS  read-write
   STATUS      current
   DESCRIPTION
       "Default:10, Range : 1-15. "
   ::= { opmen99810bSystemAccountPrivilegeLevel 39 }

opmen99810bVLANsPrivilegeLevel OBJECT-TYPE
   SYNTAX      Integer32 (1..15)
   MAX-ACCESS  read-write
   STATUS      current
   DESCRIPTION
       "Default:10, Range : 1-15. "
   ::= { opmen99810bSystemAccountPrivilegeLevel 41 }

opmen99810bVoiceVLANPrivilegeLevel OBJECT-TYPE
   SYNTAX      Integer32 (1..15)
   MAX-ACCESS  read-write
   STATUS      current
   DESCRIPTION
       "Default:10, Range : 1-15. "
   ::= { opmen99810bSystemAccountPrivilegeLevel 42 }

opmen99810bIP                                                    OBJECT IDENTIFIER ::= { opmen99810bSystem 4 }

opmen99810bIPv4                                                  OBJECT IDENTIFIER ::= { opmen99810bIP 1 }

opmen99810bIPv4Configured                                                  OBJECT IDENTIFIER ::= { opmen99810bIPv4 1 }

opmen99810bIpv4DHCPClient OBJECT-TYPE
   SYNTAX      INTEGER { disable(0), enable(1) }
   MAX-ACCESS  read-write
   STATUS      current
   DESCRIPTION
       "default:0
       0: disable
       1: enable"
   ::= { opmen99810bIPv4Configured 1 }

opmen99810bIPv4Address OBJECT-TYPE
   SYNTAX      IpAddress
   MAX-ACCESS  read-write
   STATUS      current
   DESCRIPTION
       ""
   ::= { opmen99810bIPv4Configured 2 }

opmen99810bIPv4Mask OBJECT-TYPE
   SYNTAX      IpAddress
   MAX-ACCESS  read-write
   STATUS      current
   DESCRIPTION
       ""
   ::= { opmen99810bIPv4Configured 3 }

opmen99810bIPv4Gateway OBJECT-TYPE
   SYNTAX      IpAddress
   MAX-ACCESS  read-write
   STATUS      current
   DESCRIPTION
       ""
   ::= { opmen99810bIPv4Configured 4 }

opmen99810bIPv4VLANId OBJECT-TYPE
   SYNTAX      Integer32(1..4094)
   MAX-ACCESS  read-write
   STATUS      current
   DESCRIPTION
       "default:1"
   ::= { opmen99810bIPv4Configured 5 }

opmen99810bIPv4DNSServer OBJECT-TYPE
   SYNTAX      IpAddress
   MAX-ACCESS  read-write
   STATUS      current
   DESCRIPTION
       ""
   ::= { opmen99810bIPv4Configured 6 }

opmen99810bIPv4DNSProxy OBJECT-TYPE
   SYNTAX      INTEGER { disable(0), enable(1) }
   MAX-ACCESS  read-write
   STATUS      current
   DESCRIPTION
       "0:disable, 1:enable "
   ::= { opmen99810bIPv4Configured 7 }

opmen99810bIPv4Current                                                  OBJECT IDENTIFIER ::= { opmen99810bIPv4 2 }

opmen99810bIpv4CurrentDHCPClient OBJECT-TYPE
   SYNTAX      INTEGER { none(0), renew(1) }
   MAX-ACCESS  read-write
   STATUS      current
   DESCRIPTION
       "default:0
       0: none (for read)
       1: renew"
   ::= { opmen99810bIPv4Current 1 }

opmen99810bIPv4CurrentAddress OBJECT-TYPE
   SYNTAX      IpAddress
   MAX-ACCESS  read-only
   STATUS      current
   DESCRIPTION
       ""
   ::= { opmen99810bIPv4Current 2 }

opmen99810bIPv4CurrentMask OBJECT-TYPE
   SYNTAX      IpAddress
   MAX-ACCESS  read-only
   STATUS      current
   DESCRIPTION
       ""
   ::= { opmen99810bIPv4Current 3 }

opmen99810bIPv4CurrentGateway OBJECT-TYPE
   SYNTAX      IpAddress
   MAX-ACCESS  read-only
   STATUS      current
   DESCRIPTION
       ""
   ::= { opmen99810bIPv4Current 4 }

opmen99810bIPv4CurrentVLANId OBJECT-TYPE
   SYNTAX      Integer32(1..4094)
   MAX-ACCESS  read-only
   STATUS      current
   DESCRIPTION
       "default:1"
   ::= { opmen99810bIPv4Current 5 }

opmen99810bIPv4CurrentDNSServer OBJECT-TYPE
   SYNTAX      IpAddress
   MAX-ACCESS  read-only
   STATUS      current
   DESCRIPTION
       ""
   ::= { opmen99810bIPv4Current 6 }


opmen99810bIPv6                                                  OBJECT IDENTIFIER ::= { opmen99810bIP 2 }

opmen99810bIPv6Configured                                                  OBJECT IDENTIFIER ::= { opmen99810bIPv6 1 }

opmen99810bIpv6AutoConfiguration OBJECT-TYPE
   SYNTAX      INTEGER { disable(0), enable(1) }
   MAX-ACCESS  read-write
   STATUS      current
   DESCRIPTION
       "default:0
       0: disable
       1: enable"
   ::= { opmen99810bIPv6Configured 1 }

opmen99810bIpv6Address OBJECT-TYPE
   SYNTAX      DisplayString (SIZE (0..30))
   MAX-ACCESS  read-write
   STATUS      current
   DESCRIPTION
       ""
   ::= { opmen99810bIPv6Configured 2 }

opmen99810bIpv6Prefix OBJECT-TYPE
   SYNTAX      Integer32 (1..128)
   MAX-ACCESS  read-write
   STATUS      current
   DESCRIPTION
       "default: 96"
   ::= { opmen99810bIPv6Configured 3 }

opmen99810bIpv6Gateway OBJECT-TYPE
   SYNTAX      DisplayString (SIZE (0..30))
   MAX-ACCESS  read-write
   STATUS      current
   DESCRIPTION
       " "
   ::= { opmen99810bIPv6Configured 4 }

opmen99810bIPv6Current                                                  OBJECT IDENTIFIER ::= { opmen99810bIPv6 2 }

opmen99810bIpv6CurrentAutoConfiguration OBJECT-TYPE
   SYNTAX      INTEGER { disable(0), enable(1) }
   MAX-ACCESS  read-only
   STATUS      current
   DESCRIPTION
       "default:0
       0: disable
       1: enable"
   ::= { opmen99810bIPv6Current 1 }

opmen99810bIpv6CurrentAddress OBJECT-TYPE
   SYNTAX      DisplayString (SIZE (0..30))
   MAX-ACCESS  read-only
   STATUS      current
   DESCRIPTION
       ""
   ::= { opmen99810bIPv6Current 2 }


opmen99810bIpv6CurrentLinkLocalAddress OBJECT-TYPE
   SYNTAX      DisplayString(SIZE (0..30))
   MAX-ACCESS  read-only
   STATUS      current
   DESCRIPTION
       ""
   ::= { opmen99810bIPv6Current 3 }


opmen99810bIpv6CurrentPrefix OBJECT-TYPE
   SYNTAX      Integer32(1..128)
   MAX-ACCESS  read-only
   STATUS      current
   DESCRIPTION
       ""
   ::= { opmen99810bIPv6Current 4 }

opmen99810bIpv6CurrentGateway OBJECT-TYPE
   SYNTAX      DisplayString (SIZE (0..30))
   MAX-ACCESS  read-only
   STATUS      current
   DESCRIPTION
       " "
   ::= { opmen99810bIPv6Current 5 }

opmen99810bSyslog                                                OBJECT IDENTIFIER ::= { opmen99810bSystem 5 }

opmen99810bSyslogConf                                            OBJECT IDENTIFIER ::= { opmen99810bSyslog 1 }

opmen99810bServerMode OBJECT-TYPE
   SYNTAX      INTEGER { disable(0), enable(1) }
   MAX-ACCESS  read-write
   STATUS      current
   DESCRIPTION
       "default: 0
       0: disable
       1: enable "
   ::= { opmen99810bSyslogConf 1 }

opmen99810bServerAddress1 OBJECT-TYPE
   SYNTAX      IpAddress
   MAX-ACCESS  read-write
   STATUS      current
   DESCRIPTION
       " "
   ::= { opmen99810bSyslogConf 2 }

opmen99810bServerAddress2 OBJECT-TYPE
   SYNTAX      IpAddress
   MAX-ACCESS  read-write
   STATUS      current
   DESCRIPTION
       " "
   ::= { opmen99810bSyslogConf 3 }

opmen99810bSyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { opmen99810bSyslogConf 4 }

opmen99810bSyslogDetailedInfo                                    OBJECT IDENTIFIER ::= { opmen99810bSyslog 2 }

opmen99810bSyslogDetailedInfoClear OBJECT-TYPE
   SYNTAX      INTEGER { none(0), clear(1) }
   MAX-ACCESS  read-write
   STATUS      current
   DESCRIPTION
      "default: 0
       0 : None  (read only)
       1 : Clear Syslog"
   ::= { opmen99810bSyslogDetailedInfo 1 }

opmen99810bSyslogDetailedInfoTable OBJECT-TYPE
  SYNTAX      SEQUENCE OF Opmen99810bSyslogDetailedInfoEntry
  MAX-ACCESS  not-accessible
  STATUS      current
  DESCRIPTION
           " "
       ::= { opmen99810bSyslogDetailedInfo 2 }

opmen99810bSyslogDetailedInfoEntry OBJECT-TYPE
   SYNTAX      Opmen99810bSyslogDetailedInfoEntry
   MAX-ACCESS  not-accessible
   STATUS      current
   DESCRIPTION
           ""
   INDEX    { opmen99810bSyslogDetailedInfoIndex  }
   ::= { opmen99810bSyslogDetailedInfoTable 1 }

Opmen99810bSyslogDetailedInfoEntry ::= SEQUENCE {
   opmen99810bSyslogDetailedInfoIndex       Integer32,
   opmen99810bSyslogDetailedInfoLevel       DisplayString,
   opmen99810bSyslogDetailedInfoTime        DisplayString,
   opmen99810bSyslogDetailedInfoMessage     DisplayString
}

opmen99810bSyslogDetailedInfoIndex OBJECT-TYPE
   SYNTAX      Integer32(1..1024)
   MAX-ACCESS  not-accessible
   STATUS      current
   DESCRIPTION
       " "
   ::= { opmen99810bSyslogDetailedInfoEntry 1 }

opmen99810bSyslogDetailedInfoLevel OBJECT-TYPE
   SYNTAX      DisplayString
   MAX-ACCESS  read-only
   STATUS      current
   DESCRIPTION
       " "
   ::= { opmen99810bSyslogDetailedInfoEntry 2 }

opmen99810bSyslogDetailedInfoTime OBJECT-TYPE
   SYNTAX      DisplayString(SIZE (0..20))
   MAX-ACCESS  read-only
   STATUS      current
   DESCRIPTION
       " "
   ::= { opmen99810bSyslogDetailedInfoEntry 3 }

opmen99810bSyslogDetailedInfoMessage OBJECT-TYPE
   SYNTAX      DisplayString
   MAX-ACCESS  read-only
   STATUS      current
   DESCRIPTION
       " "
   ::= { opmen99810bSyslogDetailedInfoEntry 4 }


opmen99810bSnmp                                                OBJECT IDENTIFIER ::= { opmen99810bSystem 6 }

opmen99810bSnmpConf                                            OBJECT IDENTIFIER ::= { opmen99810bSnmp 1 }

opmen99810bGetCommunity OBJECT-TYPE
   SYNTAX       DisplayString
   MAX-ACCESS   read-write
   STATUS       current
   DESCRIPTION
       "Get/Set the get-community of the SNMP."
   ::= { opmen99810bSnmpConf 1 }

opmen99810bSetCommunityMode OBJECT-TYPE
   SYNTAX       INTEGER { disable(0), enable(1) }
   MAX-ACCESS   read-write
   STATUS       current
   DESCRIPTION
       "Get/Set the set-community mode of the SNMP.
        default : 1, 0: disable, 1: enable. "
   ::= { opmen99810bSnmpConf 2 }

opmen99810bSetCommunity OBJECT-TYPE
   SYNTAX       DisplayString
   MAX-ACCESS   read-write
   STATUS       current
   DESCRIPTION
       "Get/Set the set-community of the SNMP."
   ::= { opmen99810bSnmpConf 3 }

opmen99810bTrapHostConfTable OBJECT-TYPE
   SYNTAX      SEQUENCE OF Opmen99810bTrapHostConfEntry
   MAX-ACCESS  not-accessible
   STATUS      current
   DESCRIPTION
       "A list of trap host entry. The numbers of entries are given by the value of opmen99810bTrapHostConfNumber."
   ::= { opmen99810bSnmpConf 4 }

opmen99810bTrapHostConfEntry OBJECT-TYPE
   SYNTAX      Opmen99810bTrapHostConfEntry
   MAX-ACCESS  not-accessible
   STATUS      current
   DESCRIPTION
       "This is the entry information for trap host."
   INDEX    { opmen99810bTrapHostConfIndex  }
   ::= { opmen99810bTrapHostConfTable 1 }

Opmen99810bTrapHostConfEntry ::= SEQUENCE {
    opmen99810bTrapHostConfIndex             Integer32,
    opmen99810bTrapHostConfVersion           INTEGER,
    opmen99810bTrapHostConfIPType            INTEGER,
    opmen99810bTrapHostConfIP                DisplayString,
    opmen99810bTrapHostConfPort              Integer32,
    opmen99810bTrapHostConfCommunity         DisplayString,
    opmen99810bTrapHostConfSeverityLevel     INTEGER,
    opmen99810bTrapHostConfSecurityLevel     INTEGER,
    opmen99810bTrapHostConfAuthPtc           INTEGER,
    opmen99810bTrapHostConfAuthPassword      DisplayString,
    opmen99810bTrapHostConfPrivPtc           INTEGER,
    opmen99810bTrapHostConfPrivPassword      DisplayString,
    opmen99810bTrapHostConfCurrentMode       INTEGER
}

opmen99810bTrapHostConfIndex OBJECT-TYPE
   SYNTAX      Integer32(1..6)
   MAX-ACCESS  not-accessible
   STATUS      current
   DESCRIPTION
       " The index of the trap host entry. "
   ::= { opmen99810bTrapHostConfEntry 1 }

opmen99810bTrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { opmen99810bTrapHostConfEntry 2 }

opmen99810bTrapHostConfIPType OBJECT-TYPE
   SYNTAX       INTEGER { ipv4(4), ipv6(6) }
   MAX-ACCESS   read-write
   STATUS       current
   DESCRIPTION
       "Server IP Type. Default: 4,
        4 : IPv4,
        6 : IPv6."
   ::= { opmen99810bTrapHostConfEntry 3 }

opmen99810bTrapHostConfIP OBJECT-TYPE
   SYNTAX       DisplayString
   MAX-ACCESS   read-write
   STATUS       current
   DESCRIPTION
       "This is the IP of the trap host."
   ::= { opmen99810bTrapHostConfEntry 4 }

opmen99810bTrapHostConfPort OBJECT-TYPE
   SYNTAX       Integer32(1..65535)
   MAX-ACCESS   read-write
   STATUS       current
   DESCRIPTION
       "This is the receiving-port number of the trap host.
        range : 1 - 65535."
   ::= { opmen99810bTrapHostConfEntry 5 }

opmen99810bTrapHostConfCommunity OBJECT-TYPE
   SYNTAX       DisplayString (SIZE (1..32))
   MAX-ACCESS   read-write
   STATUS       current
   DESCRIPTION
       "The community/security name for the trap PDU."
   ::= { opmen99810bTrapHostConfEntry 6 }

opmen99810bTrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { opmen99810bTrapHostConfEntry 7 }

opmen99810bTrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { opmen99810bTrapHostConfEntry 8 }

opmen99810bTrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { opmen99810bTrapHostConfEntry 9 }

opmen99810bTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { opmen99810bTrapHostConfEntry 10 }

opmen99810bTrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { opmen99810bTrapHostConfEntry 11 }

opmen99810bTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { opmen99810bTrapHostConfEntry 12 }

opmen99810bTrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { opmen99810bTrapHostConfEntry 13 }


----------------------------------------------------------------------------------------------------

opmen99810bConfiguration                                         OBJECT IDENTIFIER ::= { opmen99810bProductId 2 }

opmen99810bPort                                                  OBJECT IDENTIFIER ::= { opmen99810bConfiguration 1 }

opmen99810bPortConfigurationTable OBJECT-TYPE
   SYNTAX      SEQUENCE OF Opmen99810bPortConfigurationEntry
   MAX-ACCESS  not-accessible
   STATUS      current
   DESCRIPTION
       " Show port configurations. "
   ::= { opmen99810bPort 1 }

opmen99810bPortConfigurationEntry OBJECT-TYPE
   SYNTAX      Opmen99810bPortConfigurationEntry
   MAX-ACCESS  not-accessible
   STATUS      current
   DESCRIPTION
       ""
   INDEX    { opmen99810bPortConfPort  }
   ::= { opmen99810bPortConfigurationTable 1 }

Opmen99810bPortConfigurationEntry ::= SEQUENCE {
   opmen99810bPortConfPort                     Integer32,
   opmen99810bPortConfPortMedia                DisplayString,
   opmen99810bPortConfLink                     DisplayString,
   opmen99810bPortConfCurrentSpeed             DisplayString,
   opmen99810bPortConfSpeed                    INTEGER,
   opmen99810bPortConfCurrentFlowControlRx     INTEGER,
   opmen99810bPortConfCurrentFlowControlTx     INTEGER,
   opmen99810bPortConfFlowControl              INTEGER,
   opmen99810bPortConfMaxFrameSize             Integer32,
   opmen99810bPortConfExcessiveCollisionMode   INTEGER,
   opmen99810bPortConfPowerControl             INTEGER,
   opmen99810bPortConfDescription              DisplayString
}

opmen99810bPortConfPort OBJECT-TYPE
   SYNTAX      Integer32(1..4095)
   MAX-ACCESS  not-accessible
   STATUS      current
   DESCRIPTION
       " port, range : 1 - port number. "
   ::= { opmen99810bPortConfigurationEntry 1 }

opmen99810bPortConfPortMedia OBJECT-TYPE
   SYNTAX      DisplayString(SIZE (1..4))
   MAX-ACCESS  read-only
   STATUS      current
   DESCRIPTION
       " Show port media. "
   ::= { opmen99810bPortConfigurationEntry 2 }

opmen99810bPortConfLink OBJECT-TYPE
   SYNTAX      DisplayString(SIZE (2..4))
   MAX-ACCESS  read-only
   STATUS      current
   DESCRIPTION
       " The current link state. "
   ::= { opmen99810bPortConfigurationEntry 3 }

opmen99810bPortConfCurrentSpeed OBJECT-TYPE
   SYNTAX      DisplayString(SIZE (6..12))
   MAX-ACCESS  read-only
   STATUS      current
   DESCRIPTION
       " The current link speed of the port. "
   ::= { opmen99810bPortConfigurationEntry 4 }

opmen99810bPortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11)
                }
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X "
   ::= { opmen99810bPortConfigurationEntry 5 }

opmen99810bPortConfCurrentFlowControlRx OBJECT-TYPE
   SYNTAX      INTEGER { disable(0), enable(1), noSupport(2) }
   MAX-ACCESS  read-only
   STATUS      current
   DESCRIPTION
       "0: disable
        1: enable
        2: no support.  "
   ::= { opmen99810bPortConfigurationEntry 6 }

opmen99810bPortConfCurrentFlowControlTx OBJECT-TYPE
   SYNTAX      INTEGER { disable(0), enable(1), noSupport(2) }
   MAX-ACCESS  read-only
   STATUS      current
   DESCRIPTION
       "0: disable
        1: enable
        2: no support.  "
   ::= { opmen99810bPortConfigurationEntry 7 }

opmen99810bPortConfFlowControl OBJECT-TYPE
   SYNTAX      INTEGER { disable(0), enable(1), noSupport(2) }
   MAX-ACCESS  read-write
   STATUS      current
   DESCRIPTION
       "default: 0,
        0: disable
        1: enable
        2: no support. "
   ::= { opmen99810bPortConfigurationEntry 8 }

opmen99810bPortConfMaxFrameSize OBJECT-TYPE
   SYNTAX      Integer32 (1518..9600)
   MAX-ACCESS  read-write
   STATUS      current
   DESCRIPTION
       "default: 9600 , range : 1518 - 9600 "
   ::= { opmen99810bPortConfigurationEntry 9 }

opmen99810bPortConfExcessiveCollisionMode OBJECT-TYPE
   SYNTAX      INTEGER { discard(0), restart(1), noSupport(2) }
   MAX-ACCESS  read-write
   STATUS      current
   DESCRIPTION
       "default: 0,
        Excessive Collision Mode :
        0: Discard,
        1: Restart,
        2: no support.
       "
   ::= { opmen99810bPortConfigurationEntry 10 }

opmen99810bPortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy,
        2: Dynamic (perfectReach),
        3: Enable,
        4: no support.
       "
   ::= { opmen99810bPortConfigurationEntry 11 }

opmen99810bPortConfDescription OBJECT-TYPE
   SYNTAX      DisplayString
   MAX-ACCESS  read-write
   STATUS      current
   DESCRIPTION
       " Interface specific description.
         Up to 47 characters describing this interface. "
   ::= { opmen99810bPortConfigurationEntry 12 }


opmen99810bPortTrafficStatisticsTable OBJECT-TYPE
   SYNTAX      SEQUENCE OF Opmen99810bPortTrafficStatisticsEntry
   MAX-ACCESS  not-accessible
   STATUS      current
   DESCRIPTION
       " "
   ::= { opmen99810bPort 2 }

opmen99810bPortTrafficStatisticsEntry OBJECT-TYPE
   SYNTAX      Opmen99810bPortTrafficStatisticsEntry
   MAX-ACCESS  not-accessible
   STATUS      current
   DESCRIPTION
       ""
   INDEX    { opmen99810bPortTrafficStatisticsPort  }
   ::= { opmen99810bPortTrafficStatisticsTable 1 }

Opmen99810bPortTrafficStatisticsEntry ::= SEQUENCE {
   opmen99810bPortTrafficStatisticsPort          Integer32,
   opmen99810bPortTrafficStatisticsClear         INTEGER,
   opmen99810bPortTrafficRxPackets               Counter64,
   opmen99810bPortTrafficRxOctets                Counter64,
   opmen99810bPortTrafficRxUnicast               Counter64,
   opmen99810bPortTrafficRxMulticast             Counter64,
   opmen99810bPortTrafficRxBroadcast             Counter64,
   opmen99810bPortTrafficRxPause                 Counter64,
   opmen99810bPortTrafficRx64Bytes               Counter64,
   opmen99810bPortTrafficRx65to127Bytes          Counter64,
   opmen99810bPortTrafficRx128to255Bytes         Counter64,
   opmen99810bPortTrafficRx256to511Bytes         Counter64,
   opmen99810bPortTrafficRx512to1023Bytes        Counter64,
   opmen99810bPortTrafficRx1024to1526Bytes       Counter64,
   opmen99810bPortTrafficRxExceecd1527Bytes      Counter64,
   opmen99810bPortTrafficRxQ0                    Counter64,
   opmen99810bPortTrafficRxQ1                    Counter64,
   opmen99810bPortTrafficRxQ2                    Counter64,
   opmen99810bPortTrafficRxQ3                    Counter64,
   opmen99810bPortTrafficRxQ4                    Counter64,
   opmen99810bPortTrafficRxQ5                    Counter64,
   opmen99810bPortTrafficRxQ6                    Counter64,
   opmen99810bPortTrafficRxQ7                    Counter64,
   opmen99810bPortTrafficRxDrops                 Counter64,
   opmen99810bPortTrafficRxCRCorAlignment        Counter64,
   opmen99810bPortTrafficRxUndersize             Counter64,
   opmen99810bPortTrafficRxOversize              Counter64,
   opmen99810bPortTrafficRxFragments             Counter64,
   opmen99810bPortTrafficRxJabber                Counter64,
   opmen99810bPortTrafficRxFiltered              Counter64,
   opmen99810bPortTrafficTxPackets               Counter64,
   opmen99810bPortTrafficTxOctets                Counter64,
   opmen99810bPortTrafficTxUnicast               Counter64,
   opmen99810bPortTrafficTxMulticast             Counter64,
   opmen99810bPortTrafficTxBroadcast             Counter64,
   opmen99810bPortTrafficTxPause                 Counter64,
   opmen99810bPortTrafficTx64Bytes               Counter64,
   opmen99810bPortTrafficTx65to127Bytes          Counter64,
   opmen99810bPortTrafficTx128to255Bytes         Counter64,
   opmen99810bPortTrafficTx256to511Bytes         Counter64,
   opmen99810bPortTrafficTx512to1023Bytes        Counter64,
   opmen99810bPortTrafficTx1024to1526Bytes       Counter64,
   opmen99810bPortTrafficTxExceecd1527Bytes      Counter64,
   opmen99810bPortTrafficTxQ0                    Counter64,
   opmen99810bPortTrafficTxQ1                    Counter64,
   opmen99810bPortTrafficTxQ2                    Counter64,
   opmen99810bPortTrafficTxQ3                    Counter64,
   opmen99810bPortTrafficTxQ4                    Counter64,
   opmen99810bPortTrafficTxQ5                    Counter64,
   opmen99810bPortTrafficTxQ6                    Counter64,
   opmen99810bPortTrafficTxQ7                    Counter64,
   opmen99810bPortTrafficTxDrops                 Counter64,
   opmen99810bPortTrafficTxLateOrExcColl         Counter64
}

opmen99810bPortTrafficStatisticsPort OBJECT-TYPE
   SYNTAX      Integer32 (1..4095)
   MAX-ACCESS  not-accessible
   STATUS      current
   DESCRIPTION
       " "
   ::= { opmen99810bPortTrafficStatisticsEntry 1 }

opmen99810bPortTrafficStatisticsClear OBJECT-TYPE
   SYNTAX      INTEGER { disable(0), enable(1) }
   MAX-ACCESS  read-write
   STATUS      current
   DESCRIPTION
       " "
   ::= { opmen99810bPortTrafficStatisticsEntry 2 }

opmen99810bPortTrafficRxPackets OBJECT-TYPE
   SYNTAX      Counter64
   MAX-ACCESS  read-only
   STATUS      current
   DESCRIPTION
       " "
   ::= { opmen99810bPortTrafficStatisticsEntry 3 }

opmen99810bPortTrafficRxOctets OBJECT-TYPE
   SYNTAX      Counter64
   MAX-ACCESS  read-only
   STATUS      current
   DESCRIPTION
       " "
   ::= { opmen99810bPortTrafficStatisticsEntry 4 }

opmen99810bPortTrafficRxUnicast OBJECT-TYPE
   SYNTAX      Counter64
   MAX-ACCESS  read-only
   STATUS      current
   DESCRIPTION
       " "
   ::= { opmen99810bPortTrafficStatisticsEntry 5 }

opmen99810bPortTrafficRxMulticast OBJECT-TYPE
   SYNTAX      Counter64
   MAX-ACCESS  read-only
   STATUS      current
   DESCRIPTION
       " "
   ::= { opmen99810bPortTrafficStatisticsEntry 6 }

opmen99810bPortTrafficRxBroadcast OBJECT-TYPE
   SYNTAX      Counter64
   MAX-ACCESS  read-only
   STATUS      current
   DESCRIPTION
       " "
   ::= { opmen99810bPortTrafficStatisticsEntry 7 }

opmen99810bPortTrafficRxPause OBJECT-TYPE
   SYNTAX      Counter64
   MAX-ACCESS  read-only
   STATUS      current
   DESCRIPTION
       " "
   ::= { opmen99810bPortTrafficStatisticsEntry 8 }

opmen99810bPortTrafficRx64Bytes OBJECT-TYPE
   SYNTAX      Counter64
   MAX-ACCESS  read-only
   STATUS      current
   DESCRIPTION
       " "
   ::= { opmen99810bPortTrafficStatisticsEntry 9 }

opmen99810bPortTrafficRx65to127Bytes OBJECT-TYPE
   SYNTAX      Counter64
   MAX-ACCESS  read-only
   STATUS      current
   DESCRIPTION
       " "
   ::= { opmen99810bPortTrafficStatisticsEntry 10 }

opmen99810bPortTrafficRx128to255Bytes OBJECT-TYPE
   SYNTAX      Counter64
   MAX-ACCESS  read-only
   STATUS      current
   DESCRIPTION
       " "
   ::= { opmen99810bPortTrafficStatisticsEntry 11 }

opmen99810bPortTrafficRx256to511Bytes OBJECT-TYPE
   SYNTAX      Counter64
   MAX-ACCESS  read-only
   STATUS      current
   DESCRIPTION
       " "
   ::= { opmen99810bPortTrafficStatisticsEntry 12 }

opmen99810bPortTrafficRx512to1023Bytes OBJECT-TYPE
   SYNTAX      Counter64
   MAX-ACCESS  read-only
   STATUS      current
   DESCRIPTION
       " "
   ::= { opmen99810bPortTrafficStatisticsEntry 13 }

opmen99810bPortTrafficRx1024to1526Bytes OBJECT-TYPE
   SYNTAX      Counter64
   MAX-ACCESS  read-only
   STATUS      current
   DESCRIPTION
       " "
   ::= { opmen99810bPortTrafficStatisticsEntry 14 }

opmen99810bPortTrafficRxExceecd1527Bytes OBJECT-TYPE
   SYNTAX      Counter64
   MAX-ACCESS  read-only
   STATUS      current
   DESCRIPTION
       " "
   ::= { opmen99810bPortTrafficStatisticsEntry 15 }

opmen99810bPortTrafficRxQ0 OBJECT-TYPE
   SYNTAX      Counter64
   MAX-ACCESS  read-only
   STATUS      current
   DESCRIPTION
       " "
   ::= { opmen99810bPortTrafficStatisticsEntry 16 }

opmen99810bPortTrafficRxQ1 OBJECT-TYPE
   SYNTAX      Counter64
   MAX-ACCESS  read-only
   STATUS      current
   DESCRIPTION
       " "
   ::= { opmen99810bPortTrafficStatisticsEntry 17 }

opmen99810bPortTrafficRxQ2 OBJECT-TYPE
   SYNTAX      Counter64
   MAX-ACCESS  read-only
   STATUS      current
   DESCRIPTION
       " "
   ::= { opmen99810bPortTrafficStatisticsEntry 18 }

opmen99810bPortTrafficRxQ3 OBJECT-TYPE
   SYNTAX      Counter64
   MAX-ACCESS  read-only
   STATUS      current
   DESCRIPTION
       " "
   ::= { opmen99810bPortTrafficStatisticsEntry 19 }

opmen99810bPortTrafficRxQ4 OBJECT-TYPE
   SYNTAX      Counter64
   MAX-ACCESS  read-only
   STATUS      current
   DESCRIPTION
       " "
   ::= { opmen99810bPortTrafficStatisticsEntry 20 }

opmen99810bPortTrafficRxQ5 OBJECT-TYPE
   SYNTAX      Counter64
   MAX-ACCESS  read-only
   STATUS      current
   DESCRIPTION
       " "
   ::= { opmen99810bPortTrafficStatisticsEntry 21 }

opmen99810bPortTrafficRxQ6 OBJECT-TYPE
   SYNTAX      Counter64
   MAX-ACCESS  read-only
   STATUS      current
   DESCRIPTION
       " "
   ::= { opmen99810bPortTrafficStatisticsEntry 22 }

opmen99810bPortTrafficRxQ7 OBJECT-TYPE
   SYNTAX      Counter64
   MAX-ACCESS  read-only
   STATUS      current
   DESCRIPTION
       " "
   ::= { opmen99810bPortTrafficStatisticsEntry 23 }

opmen99810bPortTrafficRxDrops OBJECT-TYPE
   SYNTAX      Counter64
   MAX-ACCESS  read-only
   STATUS      current
   DESCRIPTION
       " "
   ::= { opmen99810bPortTrafficStatisticsEntry 24 }

opmen99810bPortTrafficRxCRCorAlignment OBJECT-TYPE
   SYNTAX      Counter64
   MAX-ACCESS  read-only
   STATUS      current
   DESCRIPTION
       " "
   ::= { opmen99810bPortTrafficStatisticsEntry 25 }

opmen99810bPortTrafficRxUndersize OBJECT-TYPE
   SYNTAX      Counter64
   MAX-ACCESS  read-only
   STATUS      current
   DESCRIPTION
       " "
   ::= { opmen99810bPortTrafficStatisticsEntry 26 }

opmen99810bPortTrafficRxOversize OBJECT-TYPE
   SYNTAX      Counter64
   MAX-ACCESS  read-only
   STATUS      current
   DESCRIPTION
       " "
   ::= { opmen99810bPortTrafficStatisticsEntry 27 }

opmen99810bPortTrafficRxFragments OBJECT-TYPE
   SYNTAX      Counter64
   MAX-ACCESS  read-only
   STATUS      current
   DESCRIPTION
       " "
   ::= { opmen99810bPortTrafficStatisticsEntry 28 }

opmen99810bPortTrafficRxJabber OBJECT-TYPE
   SYNTAX      Counter64
   MAX-ACCESS  read-only
   STATUS      current
   DESCRIPTION
       " "
   ::= { opmen99810bPortTrafficStatisticsEntry 29 }

opmen99810bPortTrafficRxFiltered OBJECT-TYPE
   SYNTAX      Counter64
   MAX-ACCESS  read-only
   STATUS      current
   DESCRIPTION
       " "
   ::= { opmen99810bPortTrafficStatisticsEntry 30 }

opmen99810bPortTrafficTxPackets OBJECT-TYPE
   SYNTAX      Counter64
   MAX-ACCESS  read-only
   STATUS      current
   DESCRIPTION
       " "
   ::= { opmen99810bPortTrafficStatisticsEntry 31 }

opmen99810bPortTrafficTxOctets OBJECT-TYPE
   SYNTAX      Counter64
   MAX-ACCESS  read-only
   STATUS      current
   DESCRIPTION
       " "
   ::= { opmen99810bPortTrafficStatisticsEntry 32 }

opmen99810bPortTrafficTxUnicast OBJECT-TYPE
   SYNTAX      Counter64
   MAX-ACCESS  read-only
   STATUS      current
   DESCRIPTION
       " "
   ::= { opmen99810bPortTrafficStatisticsEntry 33 }

opmen99810bPortTrafficTxMulticast OBJECT-TYPE
   SYNTAX      Counter64
   MAX-ACCESS  read-only
   STATUS      current
   DESCRIPTION
       " "
   ::= { opmen99810bPortTrafficStatisticsEntry 34 }

opmen99810bPortTrafficTxBroadcast OBJECT-TYPE
   SYNTAX      Counter64
   MAX-ACCESS  read-only
   STATUS      current
   DESCRIPTION
       " "
   ::= { opmen99810bPortTrafficStatisticsEntry 35 }

opmen99810bPortTrafficTxPause OBJECT-TYPE
   SYNTAX      Counter64
   MAX-ACCESS  read-only
   STATUS      current
   DESCRIPTION
       " "
   ::= { opmen99810bPortTrafficStatisticsEntry 36 }

opmen99810bPortTrafficTx64Bytes OBJECT-TYPE
   SYNTAX      Counter64
   MAX-ACCESS  read-only
   STATUS      current
   DESCRIPTION
       " "
   ::= { opmen99810bPortTrafficStatisticsEntry 37 }

opmen99810bPortTrafficTx65to127Bytes OBJECT-TYPE
   SYNTAX      Counter64
   MAX-ACCESS  read-only
   STATUS      current
   DESCRIPTION
       " "
   ::= { opmen99810bPortTrafficStatisticsEntry 38 }

opmen99810bPortTrafficTx128to255Bytes OBJECT-TYPE
   SYNTAX      Counter64
   MAX-ACCESS  read-only
   STATUS      current
   DESCRIPTION
       " "
   ::= { opmen99810bPortTrafficStatisticsEntry 39 }

opmen99810bPortTrafficTx256to511Bytes OBJECT-TYPE
   SYNTAX      Counter64
   MAX-ACCESS  read-only
   STATUS      current
   DESCRIPTION
       " "
   ::= { opmen99810bPortTrafficStatisticsEntry 40 }

opmen99810bPortTrafficTx512to1023Bytes OBJECT-TYPE
   SYNTAX      Counter64
   MAX-ACCESS  read-only
   STATUS      current
   DESCRIPTION
       " "
   ::= { opmen99810bPortTrafficStatisticsEntry 41 }

opmen99810bPortTrafficTx1024to1526Bytes OBJECT-TYPE
   SYNTAX      Counter64
   MAX-ACCESS  read-only
   STATUS      current
   DESCRIPTION
       " "
   ::= { opmen99810bPortTrafficStatisticsEntry 42 }

opmen99810bPortTrafficTxExceecd1527Bytes OBJECT-TYPE
   SYNTAX      Counter64
   MAX-ACCESS  read-only
   STATUS      current
   DESCRIPTION
       " "
   ::= { opmen99810bPortTrafficStatisticsEntry 43 }

opmen99810bPortTrafficTxQ0 OBJECT-TYPE
   SYNTAX      Counter64
   MAX-ACCESS  read-only
   STATUS      current
   DESCRIPTION
       " "
   ::= { opmen99810bPortTrafficStatisticsEntry 44 }

opmen99810bPortTrafficTxQ1 OBJECT-TYPE
   SYNTAX      Counter64
   MAX-ACCESS  read-only
   STATUS      current
   DESCRIPTION
       " "
   ::= { opmen99810bPortTrafficStatisticsEntry 45 }

opmen99810bPortTrafficTxQ2 OBJECT-TYPE
   SYNTAX      Counter64
   MAX-ACCESS  read-only
   STATUS      current
   DESCRIPTION
       " "
   ::= { opmen99810bPortTrafficStatisticsEntry 46 }

opmen99810bPortTrafficTxQ3 OBJECT-TYPE
   SYNTAX      Counter64
   MAX-ACCESS  read-only
   STATUS      current
   DESCRIPTION
       " "
   ::= { opmen99810bPortTrafficStatisticsEntry 47 }

opmen99810bPortTrafficTxQ4 OBJECT-TYPE
   SYNTAX      Counter64
   MAX-ACCESS  read-only
   STATUS      current
   DESCRIPTION
       " "
   ::= { opmen99810bPortTrafficStatisticsEntry 48 }

opmen99810bPortTrafficTxQ5 OBJECT-TYPE
   SYNTAX      Counter64
   MAX-ACCESS  read-only
   STATUS      current
   DESCRIPTION
       " "
   ::= { opmen99810bPortTrafficStatisticsEntry 49 }

opmen99810bPortTrafficTxQ6 OBJECT-TYPE
   SYNTAX      Counter64
   MAX-ACCESS  read-only
   STATUS      current
   DESCRIPTION
       " "
   ::= { opmen99810bPortTrafficStatisticsEntry 50 }


opmen99810bPortTrafficTxQ7 OBJECT-TYPE
   SYNTAX      Counter64
   MAX-ACCESS  read-only
   STATUS      current
   DESCRIPTION
       " "
   ::= { opmen99810bPortTrafficStatisticsEntry 51 }

opmen99810bPortTrafficTxDrops OBJECT-TYPE
   SYNTAX      Counter64
   MAX-ACCESS  read-only
   STATUS      current
   DESCRIPTION
       " "
   ::= { opmen99810bPortTrafficStatisticsEntry 52 }

opmen99810bPortTrafficTxLateOrExcColl OBJECT-TYPE
   SYNTAX      Counter64
   MAX-ACCESS  read-only
   STATUS      current
   DESCRIPTION
       " "
   ::= { opmen99810bPortTrafficStatisticsEntry 53 }


opmen99810bPortQoSStatistics                                     OBJECT IDENTIFIER ::= { opmen99810bPort 3 }

opmen99810bPortQoSStatisticsClear OBJECT-TYPE
   SYNTAX      INTEGER { none(0), clear(1) }
   MAX-ACCESS  read-only
   STATUS      current
   DESCRIPTION
       "default: 0
       0: none
       1: clear "
   ::= { opmen99810bPortQoSStatistics 1 }

opmen99810bPortQoSStatisticsTable OBJECT-TYPE
   SYNTAX      SEQUENCE OF Opmen99810bPortQoSStatisticsEntry
   MAX-ACCESS  not-accessible
   STATUS      current
   DESCRIPTION
       " "
   ::= { opmen99810bPortQoSStatistics 2 }

opmen99810bPortQoSStatisticsEntry OBJECT-TYPE
   SYNTAX      Opmen99810bPortQoSStatisticsEntry
   MAX-ACCESS  not-accessible
   STATUS      current
   DESCRIPTION
       ""
   INDEX    { opmen99810bPortQoSStatisticsPort  }
   ::= { opmen99810bPortQoSStatisticsTable 1 }

Opmen99810bPortQoSStatisticsEntry ::= SEQUENCE {
   opmen99810bPortQoSStatisticsPort      Integer32,
   opmen99810bPortQoSQ0Rx                Counter64,
   opmen99810bPortQoSQ0Tx                Counter64,
   opmen99810bPortQoSQ1Rx                Counter64,
   opmen99810bPortQoSQ1Tx                Counter64,
   opmen99810bPortQoSQ2Rx                Counter64,
   opmen99810bPortQoSQ2Tx                Counter64,
   opmen99810bPortQoSQ3Rx                Counter64,
   opmen99810bPortQoSQ3Tx                Counter64,
   opmen99810bPortQoSQ4Rx                Counter64,
   opmen99810bPortQoSQ4Tx                Counter64,
   opmen99810bPortQoSQ5Rx                Counter64,
   opmen99810bPortQoSQ5Tx                Counter64,
   opmen99810bPortQoSQ6Rx                Counter64,
   opmen99810bPortQoSQ6Tx                Counter64,
   opmen99810bPortQoSQ7Rx                Counter64,
   opmen99810bPortQoSQ7Tx                Counter64
}

opmen99810bPortQoSStatisticsPort OBJECT-TYPE
   SYNTAX      Integer32(1..4095)
   MAX-ACCESS  not-accessible
   STATUS      current
   DESCRIPTION
       " "
   ::= { opmen99810bPortQoSStatisticsEntry 1 }

opmen99810bPortQoSQ0Rx OBJECT-TYPE
   SYNTAX      Counter64
   MAX-ACCESS  read-only
   STATUS      current
   DESCRIPTION
       " "
   ::= { opmen99810bPortQoSStatisticsEntry 2 }

opmen99810bPortQoSQ0Tx OBJECT-TYPE
   SYNTAX      Counter64
   MAX-ACCESS  read-only
   STATUS      current
   DESCRIPTION
       " "
   ::= { opmen99810bPortQoSStatisticsEntry 3 }

opmen99810bPortQoSQ1Rx OBJECT-TYPE
   SYNTAX      Counter64
   MAX-ACCESS  read-only
   STATUS      current
   DESCRIPTION
       " "
   ::= { opmen99810bPortQoSStatisticsEntry 4 }

opmen99810bPortQoSQ1Tx OBJECT-TYPE
   SYNTAX      Counter64
   MAX-ACCESS  read-only
   STATUS      current
   DESCRIPTION
       " "
   ::= { opmen99810bPortQoSStatisticsEntry 5 }

opmen99810bPortQoSQ2Rx OBJECT-TYPE
   SYNTAX      Counter64
   MAX-ACCESS  read-only
   STATUS      current
   DESCRIPTION
       " "
   ::= { opmen99810bPortQoSStatisticsEntry 6 }

opmen99810bPortQoSQ2Tx OBJECT-TYPE
   SYNTAX      Counter64
   MAX-ACCESS  read-only
   STATUS      current
   DESCRIPTION
       " "
   ::= { opmen99810bPortQoSStatisticsEntry 7 }

opmen99810bPortQoSQ3Rx OBJECT-TYPE
   SYNTAX      Counter64
   MAX-ACCESS  read-only
   STATUS      current
   DESCRIPTION
       " "
   ::= { opmen99810bPortQoSStatisticsEntry 8 }

opmen99810bPortQoSQ3Tx OBJECT-TYPE
   SYNTAX      Counter64
   MAX-ACCESS  read-only
   STATUS      current
   DESCRIPTION
       " "
   ::= { opmen99810bPortQoSStatisticsEntry 9 }

opmen99810bPortQoSQ4Rx OBJECT-TYPE
   SYNTAX      Counter64
   MAX-ACCESS  read-only
   STATUS      current
   DESCRIPTION
       " "
   ::= { opmen99810bPortQoSStatisticsEntry 10 }

opmen99810bPortQoSQ4Tx OBJECT-TYPE
   SYNTAX      Counter64
   MAX-ACCESS  read-only
   STATUS      current
   DESCRIPTION
       " "
   ::= { opmen99810bPortQoSStatisticsEntry 11 }

opmen99810bPortQoSQ5Rx OBJECT-TYPE
   SYNTAX      Counter64
   MAX-ACCESS  read-only
   STATUS      current
   DESCRIPTION
       " "
   ::= { opmen99810bPortQoSStatisticsEntry 12 }

opmen99810bPortQoSQ5Tx OBJECT-TYPE
   SYNTAX      Counter64
   MAX-ACCESS  read-only
   STATUS      current
   DESCRIPTION
       " "
   ::= { opmen99810bPortQoSStatisticsEntry 13 }

opmen99810bPortQoSQ6Rx OBJECT-TYPE
   SYNTAX      Counter64
   MAX-ACCESS  read-only
   STATUS      current
   DESCRIPTION
       " "
   ::= { opmen99810bPortQoSStatisticsEntry 14 }

opmen99810bPortQoSQ6Tx OBJECT-TYPE
   SYNTAX      Counter64
   MAX-ACCESS  read-only
   STATUS      current
   DESCRIPTION
       " "
   ::= { opmen99810bPortQoSStatisticsEntry 15 }

opmen99810bPortQoSQ7Rx OBJECT-TYPE
   SYNTAX      Counter64
   MAX-ACCESS  read-only
   STATUS      current
   DESCRIPTION
       " "
   ::= { opmen99810bPortQoSStatisticsEntry 16 }

opmen99810bPortQoSQ7Tx OBJECT-TYPE
   SYNTAX      Counter64
   MAX-ACCESS  read-only
   STATUS      current
   DESCRIPTION
       " "
   ::= { opmen99810bPortQoSStatisticsEntry 17 }

opmen99810bSFPInfoTable OBJECT-TYPE
   SYNTAX      SEQUENCE OF Opmen99810bSFPInfoEntry
   MAX-ACCESS  not-accessible
   STATUS      current
   DESCRIPTION
       " "
   ::= { opmen99810bPort 4 }

opmen99810bSFPInfoEntry OBJECT-TYPE
   SYNTAX      Opmen99810bSFPInfoEntry
   MAX-ACCESS  not-accessible
   STATUS      current
   DESCRIPTION
       ""
   INDEX    { opmen99810bSFPInfoIndex }
   ::= { opmen99810bSFPInfoTable 1 }

Opmen99810bSFPInfoEntry ::= SEQUENCE {
   opmen99810bSFPInfoIndex               Integer32,
   opmen99810bSFPInfoPort                DisplayString,
   opmen99810bSFPConnectorType           DisplayString,
   opmen99810bSFPFiberType               DisplayString,
   opmen99810bSFPTxCentralWavelength     DisplayString,
   opmen99810bSFPBaudRate                DisplayString,
   opmen99810bSFPVendorOUI               DisplayString,
   opmen99810bSFPVendorName              DisplayString,
   opmen99810bSFPVendorPN                DisplayString,
   opmen99810bSFPVendorRev               DisplayString,
   opmen99810bSFPVendorSN                DisplayString,
   opmen99810bSFPDateCode                DisplayString,
   opmen99810bSFPTemperature             DisplayString,
   opmen99810bSFPVcc                     DisplayString,
   opmen99810bSFPMon1Bias                DisplayString,
   opmen99810bSFPMon2TxPWR               DisplayString,
   opmen99810bSFPMon3RxPWR               DisplayString
}

opmen99810bSFPInfoIndex OBJECT-TYPE
   SYNTAX      Integer32(1..4095)
   MAX-ACCESS  not-accessible
   STATUS      current
   DESCRIPTION
       " "
   ::= { opmen99810bSFPInfoEntry 1 }

opmen99810bSFPInfoPort OBJECT-TYPE
   SYNTAX      DisplayString
   MAX-ACCESS  read-only
   STATUS      current
   DESCRIPTION
       " "
   ::= { opmen99810bSFPInfoEntry 2 }

opmen99810bSFPConnectorType OBJECT-TYPE
   SYNTAX      DisplayString
   MAX-ACCESS  read-only
   STATUS      current
   DESCRIPTION
       " "
   ::= { opmen99810bSFPInfoEntry 3 }

opmen99810bSFPFiberType OBJECT-TYPE
   SYNTAX      DisplayString
   MAX-ACCESS  read-only
   STATUS      current
   DESCRIPTION
       " "
   ::= { opmen99810bSFPInfoEntry 4 }

opmen99810bSFPTxCentralWavelength OBJECT-TYPE
   SYNTAX      DisplayString
   MAX-ACCESS  read-only
   STATUS      current
   DESCRIPTION
       " "
   ::= { opmen99810bSFPInfoEntry 5 }

opmen99810bSFPBaudRate OBJECT-TYPE
   SYNTAX      DisplayString
   MAX-ACCESS  read-only
   STATUS      current
   DESCRIPTION
       " "
   ::= { opmen99810bSFPInfoEntry 6 }

opmen99810bSFPVendorOUI OBJECT-TYPE
   SYNTAX      DisplayString
   MAX-ACCESS  read-only
   STATUS      current
   DESCRIPTION
       " "
   ::= { opmen99810bSFPInfoEntry 7 }

opmen99810bSFPVendorName OBJECT-TYPE
   SYNTAX      DisplayString
   MAX-ACCESS  read-only
   STATUS      current
   DESCRIPTION
       " "
   ::= { opmen99810bSFPInfoEntry 8 }

opmen99810bSFPVendorPN OBJECT-TYPE
   SYNTAX      DisplayString
   MAX-ACCESS  read-only
   STATUS      current
   DESCRIPTION
       " "
   ::= { opmen99810bSFPInfoEntry 9 }

opmen99810bSFPVendorRev OBJECT-TYPE
   SYNTAX      DisplayString
   MAX-ACCESS  read-only
   STATUS      current
   DESCRIPTION
       " "
   ::= { opmen99810bSFPInfoEntry 10 }

opmen99810bSFPVendorSN OBJECT-TYPE
   SYNTAX      DisplayString
   MAX-ACCESS  read-only
   STATUS      current
   DESCRIPTION
       " "
   ::= { opmen99810bSFPInfoEntry 11 }

opmen99810bSFPDateCode OBJECT-TYPE
   SYNTAX      DisplayString
   MAX-ACCESS  read-only
   STATUS      current
   DESCRIPTION
       " "
   ::= { opmen99810bSFPInfoEntry 12 }

opmen99810bSFPTemperature OBJECT-TYPE
   SYNTAX      DisplayString
   MAX-ACCESS  read-only
   STATUS      current
   DESCRIPTION
       " "
   ::= { opmen99810bSFPInfoEntry 13 }

opmen99810bSFPVcc OBJECT-TYPE
   SYNTAX      DisplayString
   MAX-ACCESS  read-only
   STATUS      current
   DESCRIPTION
       " "
   ::= { opmen99810bSFPInfoEntry 14 }

opmen99810bSFPMon1Bias OBJECT-TYPE
   SYNTAX      DisplayString
   MAX-ACCESS  read-only
   STATUS      current
   DESCRIPTION
       " "
   ::= { opmen99810bSFPInfoEntry 15 }

opmen99810bSFPMon2TxPWR OBJECT-TYPE
   SYNTAX      DisplayString
   MAX-ACCESS  read-only
   STATUS      current
   DESCRIPTION
       " "
   ::= { opmen99810bSFPInfoEntry 16 }

opmen99810bSFPMon3RxPWR OBJECT-TYPE
   SYNTAX      DisplayString
   MAX-ACCESS  read-only
   STATUS      current
   DESCRIPTION
       " "
   ::= { opmen99810bSFPInfoEntry 17 }


opmen99810bPortEEETable OBJECT-TYPE
   SYNTAX      SEQUENCE OF Opmen99810bPortEEEEntry
   MAX-ACCESS  not-accessible
   STATUS      current
   DESCRIPTION
      " "
   ::= { opmen99810bPort 5 }

opmen99810bPortEEEEntry OBJECT-TYPE
   SYNTAX      Opmen99810bPortEEEEntry
   MAX-ACCESS  not-accessible
   STATUS      current
   DESCRIPTION
       ""
   INDEX    { opmen99810bPortEEEPort }
   ::= { opmen99810bPortEEETable 1 }

Opmen99810bPortEEEEntry ::= SEQUENCE {
   opmen99810bPortEEEPort		        Integer32,
   opmen99810bPortEEEMode		        INTEGER,
   opmen99810bPortEEEUrgentQueue1		INTEGER,
   opmen99810bPortEEEUrgentQueue2		INTEGER,
   opmen99810bPortEEEUrgentQueue3		INTEGER,
   opmen99810bPortEEEUrgentQueue4		INTEGER,
   opmen99810bPortEEEUrgentQueue5		INTEGER,
   opmen99810bPortEEEUrgentQueue6		INTEGER,
   opmen99810bPortEEEUrgentQueue7		INTEGER,
   opmen99810bPortEEEUrgentQueue8		INTEGER
}

opmen99810bPortEEEPort OBJECT-TYPE
   SYNTAX      Integer32(1..4095)
   MAX-ACCESS  not-accessible
   STATUS      current
   DESCRIPTION
       " "
   ::= { opmen99810bPortEEEEntry 1 }

opmen99810bPortEEEMode OBJECT-TYPE
   SYNTAX      INTEGER { disable(0), enable(1) }
   MAX-ACCESS  read-write
   STATUS      current
   DESCRIPTION
       "default: 0
       0:disable
       1:enable "
   ::= { opmen99810bPortEEEEntry 2 }

opmen99810bPortEEEUrgentQueue1 OBJECT-TYPE
   SYNTAX      INTEGER { disable(0), enable(1) }
   MAX-ACCESS  read-write
   STATUS      current
   DESCRIPTION
       "default: 0
       0:disable
       1:enable "
   ::= { opmen99810bPortEEEEntry 3 }

opmen99810bPortEEEUrgentQueue2 OBJECT-TYPE
   SYNTAX      INTEGER { disable(0), enable(1) }
   MAX-ACCESS  read-write
   STATUS      current
   DESCRIPTION
       "default: 0
       0:disable
       1:enable "
   ::= { opmen99810bPortEEEEntry 4 }

opmen99810bPortEEEUrgentQueue3 OBJECT-TYPE
   SYNTAX      INTEGER { disable(0), enable(1) }
   MAX-ACCESS  read-write
   STATUS      current
   DESCRIPTION
       "default: 0
       0:disable
       1:enable "
   ::= { opmen99810bPortEEEEntry 5 }

opmen99810bPortEEEUrgentQueue4 OBJECT-TYPE
   SYNTAX      INTEGER { disable(0), enable(1) }
   MAX-ACCESS  read-write
   STATUS      current
   DESCRIPTION
       "default: 0
       0:disable
       1:enable "
   ::= { opmen99810bPortEEEEntry 6 }

opmen99810bPortEEEUrgentQueue5 OBJECT-TYPE
   SYNTAX      INTEGER { disable(0), enable(1) }
   MAX-ACCESS  read-write
   STATUS      current
   DESCRIPTION
       "default: 0
       0:disable
       1:enable "
   ::= { opmen99810bPortEEEEntry 7 }

opmen99810bPortEEEUrgentQueue6 OBJECT-TYPE
   SYNTAX      INTEGER { disable(0), enable(1) }
   MAX-ACCESS  read-write
   STATUS      current
   DESCRIPTION
       "default: 0
       0:disable
       1:enable "
   ::= { opmen99810bPortEEEEntry 8 }

opmen99810bPortEEEUrgentQueue7 OBJECT-TYPE
   SYNTAX      INTEGER { disable(0), enable(1) }
   MAX-ACCESS  read-write
   STATUS      current
   DESCRIPTION
       "default: 0
       0:disable
       1:enable "
   ::= { opmen99810bPortEEEEntry 9 }

opmen99810bPortEEEUrgentQueue8 OBJECT-TYPE
   SYNTAX      INTEGER { disable(0), enable(1) }
   MAX-ACCESS  read-write
   STATUS      current
   DESCRIPTION
       "default: 0
       0:disable
       1:enable "
   ::= { opmen99810bPortEEEEntry 10 }


opmen99810bVoiceVLAN                                             OBJECT IDENTIFIER ::= { opmen99810bConfiguration 2 }

opmen99810bVoiceVLANConf                                         OBJECT IDENTIFIER ::= { opmen99810bVoiceVLAN 1 }

opmen99810bVoiceVLANMode OBJECT-TYPE
   SYNTAX      INTEGER { disable(0), enable(1) }
   MAX-ACCESS  read-write
   STATUS      current
   DESCRIPTION
       " Voice VLAN mode operation.
       default: 0,
       0: disable
       1: enable"
   ::= { opmen99810bVoiceVLANConf 1 }

opmen99810bVoiceVLANVLANId OBJECT-TYPE
   SYNTAX      Integer32(1..4094)
   MAX-ACCESS  read-write
   STATUS      current
   DESCRIPTION
       "Voice VLAN ID.
        default: 1000,
        range : 1-4094. "
   ::= { opmen99810bVoiceVLANConf 2 }

opmen99810bVoiceVLANAgingTime OBJECT-TYPE
   SYNTAX      Integer32(10..1000000)
   MAX-ACCESS  read-write
   STATUS      current
   DESCRIPTION
       " Voice VLAN secure learning aging time.
         default: 86400,
         range : 10 - 10000000. "
   ::= { opmen99810bVoiceVLANConf 3 }

opmen99810bVoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { opmen99810bVoiceVLANConf 4 }


opmen99810bVoiceVLANPortTable OBJECT-TYPE
   SYNTAX      SEQUENCE OF Opmen99810bVoiceVLANPortEntry
   MAX-ACCESS  not-accessible
   STATUS      current
   DESCRIPTION
       " Show Voice Vlan configuration. "
   ::= { opmen99810bVoiceVLANConf 5 }

opmen99810bVoiceVLANPortEntry OBJECT-TYPE
   SYNTAX      Opmen99810bVoiceVLANPortEntry
   MAX-ACCESS  not-accessible
   STATUS      current
   DESCRIPTION
       ""
   INDEX    { opmen99810bVoiceVLANPort  }
   ::= { opmen99810bVoiceVLANPortTable 1 }

Opmen99810bVoiceVLANPortEntry ::= SEQUENCE {
   opmen99810bVoiceVLANPort                    Integer32,
   opmen99810bVoiceVLANPortMode                INTEGER,
   opmen99810bVoiceVLANPortSecurity            INTEGER,
   opmen99810bVoiceVLANPortDiscoveryProtocol   INTEGER
}

opmen99810bVoiceVLANPort OBJECT-TYPE
   SYNTAX      Integer32(1..4095)
   MAX-ACCESS  not-accessible
   STATUS      current
   DESCRIPTION
       " port, range : 1 - port number. "
   ::= { opmen99810bVoiceVLANPortEntry 1 }

opmen99810bVoiceVLANPortMode OBJECT-TYPE
   SYNTAX      INTEGER { disable(0), auto(1), forced(2) }
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { opmen99810bVoiceVLANPortEntry 2 }

opmen99810bVoiceVLANPortSecurity OBJECT-TYPE
   SYNTAX      INTEGER { disable(0), enable(1) }
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { opmen99810bVoiceVLANPortEntry 3 }

opmen99810bVoiceVLANPortDiscoveryProtocol OBJECT-TYPE
   SYNTAX      INTEGER { oui(0), lldp(1), both(2) }
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { opmen99810bVoiceVLANPortEntry 4 }


opmen99810bVoiceVLANOUI                                          OBJECT IDENTIFIER ::= { opmen99810bVoiceVLAN 2 }

opmen99810bVoiceVLANOUICreate OBJECT-TYPE
   SYNTAX       INTEGER { none(0), create(1) }
   MAX-ACCESS   read-write
   STATUS       current
   DESCRIPTION
       "default: 0
        0 : None  (read only)
        1 : Create an OUI entry"
   ::= { opmen99810bVoiceVLANOUI 1 }

opmen99810bVoiceVLANOUITable OBJECT-TYPE
   SYNTAX      SEQUENCE OF Opmen99810bVoiceVLANOUIEntry
   MAX-ACCESS  not-accessible
   STATUS      current
   DESCRIPTION
       " Create Voice VLAN OUI entry. Modify OUI table will
         restart auto detect OUI process. "
   ::= { opmen99810bVoiceVLANOUI 2 }

opmen99810bVoiceVLANOUIEntry OBJECT-TYPE
   SYNTAX      Opmen99810bVoiceVLANOUIEntry
   MAX-ACCESS  not-accessible
   STATUS      current
   DESCRIPTION
       ""
   INDEX    { opmen99810bVoiceVLANOUIIndex  }
   ::= { opmen99810bVoiceVLANOUITable 1 }

Opmen99810bVoiceVLANOUIEntry ::= SEQUENCE {
   opmen99810bVoiceVLANOUIIndex         Integer32,
   opmen99810bVoiceVLANTelephonyOUI     OCTET STRING,
   opmen99810bVoiceVLANDescription      DisplayString,
   opmen99810bVoiceVLANOUIRowStatus     INTEGER
}

opmen99810bVoiceVLANOUIIndex OBJECT-TYPE
   SYNTAX      Integer32(1..16)
   MAX-ACCESS  not-accessible
   STATUS      current
   DESCRIPTION
       " "
   ::= { opmen99810bVoiceVLANOUIEntry 1 }

opmen99810bVoiceVLANTelephonyOUI OBJECT-TYPE
   SYNTAX      OCTET STRING (SIZE (1..32))
   MAX-ACCESS  read-write
   STATUS      current
   DESCRIPTION
       "OUI address, format : 0a 1b 2c "
   ::= { opmen99810bVoiceVLANOUIEntry 2 }

opmen99810bVoiceVLANDescription OBJECT-TYPE
   SYNTAX      DisplayString (SIZE (1..32))
   MAX-ACCESS  read-write
   STATUS      current
   DESCRIPTION
       " Up to 32 characters describing OUI address. "
   ::= { opmen99810bVoiceVLANOUIEntry 3 }

opmen99810bVoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { opmen99810bVoiceVLANOUIEntry 4 }

opmen99810bGARP                                                   OBJECT IDENTIFIER ::= { opmen99810bConfiguration 3 }

opmen99810bGARPConfTable OBJECT-TYPE
   SYNTAX      SEQUENCE OF Opmen99810bGARPConfEntry
   MAX-ACCESS  not-accessible
   STATUS      current
   DESCRIPTION
       " "
   ::= { opmen99810bGARP 1 }

opmen99810bGARPConfEntry OBJECT-TYPE
   SYNTAX      Opmen99810bGARPConfEntry
   MAX-ACCESS  not-accessible
   STATUS      current
   DESCRIPTION
       ""
   INDEX    { opmen99810bGARPConfPort  }
   ::= { opmen99810bGARPConfTable 1 }

Opmen99810bGARPConfEntry ::= SEQUENCE {
   opmen99810bGARPConfPort           Integer32,
   opmen99810bGARPJoinTimer          Integer32,
   opmen99810bGARPLeaveTimer         Integer32,
   opmen99810bGARPLeaveAllTimer      Integer32,
   opmen99810bGARPApplicantion       INTEGER,
   opmen99810bGARPAttributeType      INTEGER,
   opmen99810bGARPApplicant          INTEGER
}

opmen99810bGARPConfPort OBJECT-TYPE
   SYNTAX      Integer32(1..4095)
   MAX-ACCESS  not-accessible
   STATUS      current
   DESCRIPTION
       " "
   ::= { opmen99810bGARPConfEntry 1 }

opmen99810bGARPJoinTimer OBJECT-TYPE
   SYNTAX      Integer32(200..1000)
   MAX-ACCESS  read-write
   STATUS      current
   DESCRIPTION
       "default: 200, range : 200 - 1000 "
   ::= { opmen99810bGARPConfEntry 2 }

opmen99810bGARPLeaveTimer OBJECT-TYPE
   SYNTAX      Integer32(600..3000)
   MAX-ACCESS  read-write
   STATUS      current
   DESCRIPTION
       "default: 600 , range : 600 - 3000"
   ::= { opmen99810bGARPConfEntry 3 }

opmen99810bGARPLeaveAllTimer OBJECT-TYPE
   SYNTAX      Integer32(10000..50000)
   MAX-ACCESS  read-write
   STATUS      current
   DESCRIPTION
       "default: 10000, range : 10000 - 50000 "
   ::= { opmen99810bGARPConfEntry 4 }

opmen99810bGARPApplicantion OBJECT-TYPE
   SYNTAX      INTEGER { gvrp(1)}
   MAX-ACCESS  read-write
   STATUS      current
   DESCRIPTION
       "default: 1
       1: GVRP"
   ::= { opmen99810bGARPConfEntry 5 }

opmen99810bGARPAttributeType OBJECT-TYPE
   SYNTAX      INTEGER { vlan(1)}
   MAX-ACCESS  read-write
   STATUS      current
   DESCRIPTION
       "default: 1
       1: VLAN"
   ::= { opmen99810bGARPConfEntry 6 }

opmen99810bGARPApplicant OBJECT-TYPE
   SYNTAX      INTEGER { participant(0), nonParticipant(1) }
   MAX-ACCESS  read-write
   STATUS      current
   DESCRIPTION
       "default: 0
       0: normal-participant
       1: non-participant"
   ::= { opmen99810bGARPConfEntry 7 }

opmen99810bGARPStatisticsTable OBJECT-TYPE
   SYNTAX      SEQUENCE OF Opmen99810bGARPStatisticsEntry
   MAX-ACCESS  not-accessible
   STATUS      current
   DESCRIPTION
       " Show the basic GARP port statistics. "
   ::= { opmen99810bGARP 2 }

opmen99810bGARPStatisticsEntry OBJECT-TYPE
   SYNTAX      Opmen99810bGARPStatisticsEntry
   MAX-ACCESS  not-accessible
   STATUS      current
   DESCRIPTION
       ""
   INDEX    { opmen99810bGARPStatisticsPort  }
   ::= { opmen99810bGARPStatisticsTable 1 }

Opmen99810bGARPStatisticsEntry ::= SEQUENCE {
   opmen99810bGARPStatisticsPort             Integer32,
   opmen99810bGARPStatisticsPeerMAC          DisplayString,
   opmen99810bGARPStatisticsFailedCount      Counter32
}

opmen99810bGARPStatisticsPort OBJECT-TYPE
   SYNTAX      Integer32(1..4095)
   MAX-ACCESS  not-accessible
   STATUS      current
   DESCRIPTION
       " port, range : 1 - port number. "
   ::= { opmen99810bGARPStatisticsEntry 1 }

opmen99810bGARPStatisticsPeerMAC OBJECT-TYPE
   SYNTAX      DisplayString
   MAX-ACCESS  read-only
   STATUS      current
   DESCRIPTION
       " Peer MAC is MAC address of the neighbour Switch from with GARP frame is received.  "
   ::= { opmen99810bGARPStatisticsEntry 2 }

opmen99810bGARPStatisticsFailedCount OBJECT-TYPE
   SYNTAX      Counter32
   MAX-ACCESS  read-only
   STATUS      current
   DESCRIPTION
       " explain Failed count here. "
   ::= { opmen99810bGARPStatisticsEntry 3 }

opmen99810bGVRP                                                   OBJECT IDENTIFIER ::= { opmen99810bConfiguration 4 }

opmen99810bGVRPConf                                                   OBJECT IDENTIFIER ::= { opmen99810bGVRP 1 }

opmen99810bGVRPMode OBJECT-TYPE
   SYNTAX      INTEGER { disable(0), enable(1) }
   MAX-ACCESS  read-write
   STATUS      current
   DESCRIPTION
       "default: 0,
        0: disable,
        1: enable. "
   ::= { opmen99810bGVRPConf 1 }

opmen99810bGVRPConfTable OBJECT-TYPE
   SYNTAX      SEQUENCE OF Opmen99810bGVRPConfEntry
   MAX-ACCESS  not-accessible
   STATUS      current
   DESCRIPTION
       " "
   ::= { opmen99810bGVRPConf 2 }

opmen99810bGVRPConfEntry OBJECT-TYPE
   SYNTAX      Opmen99810bGVRPConfEntry
   MAX-ACCESS  not-accessible
   STATUS      current
   DESCRIPTION
       ""
   INDEX    { opmen99810bGVRPConfPort  }
   ::= { opmen99810bGVRPConfTable 1 }

Opmen99810bGVRPConfEntry ::= SEQUENCE {
   opmen99810bGVRPConfPort           Integer32,
   opmen99810bGVRPConfPortMode       INTEGER,
   opmen99810bGVRPConfPortRRole      INTEGER
}

opmen99810bGVRPConfPort OBJECT-TYPE
   SYNTAX      Integer32(1..4095)
   MAX-ACCESS  not-accessible
   STATUS      current
   DESCRIPTION
       " "
   ::= { opmen99810bGVRPConfEntry 1 }

opmen99810bGVRPConfPortMode OBJECT-TYPE
   SYNTAX      INTEGER { disable(0), enable(1) }
   MAX-ACCESS  read-write
   STATUS      current
   DESCRIPTION
       "default: 0
       1: enable
       0: disable"
   ::= { opmen99810bGVRPConfEntry 2 }

opmen99810bGVRPConfPortRRole OBJECT-TYPE
   SYNTAX      INTEGER { disable(0), enable(1) }
   MAX-ACCESS  read-write
   STATUS      current
   DESCRIPTION
       "default: 0
       1: enable
       0: disable"
   ::= { opmen99810bGVRPConfEntry 3 }

opmen99810bGVRPStatisticsTable OBJECT-TYPE
   SYNTAX      SEQUENCE OF Opmen99810bGVRPStatisticsEntry
   MAX-ACCESS  not-accessible
   STATUS      current
   DESCRIPTION
       " "
   ::= { opmen99810bGVRP 2 }

opmen99810bGVRPStatisticsEntry OBJECT-TYPE
   SYNTAX      Opmen99810bGVRPStatisticsEntry
   MAX-ACCESS  not-accessible
   STATUS      current
   DESCRIPTION
       ""
   INDEX    { opmen99810bGVRPStatisticsPort  }
   ::= { opmen99810bGVRPStatisticsTable 1 }

Opmen99810bGVRPStatisticsEntry ::= SEQUENCE {
   opmen99810bGVRPStatisticsPort         Integer32,
   opmen99810bGVRPStatisticsJoinTxCnt    Counter32,
   opmen99810bGVRPStatisticsLeaveTxCnt   Counter32
}

opmen99810bGVRPStatisticsPort OBJECT-TYPE
   SYNTAX      Integer32(1..4095)
   MAX-ACCESS  not-accessible
   STATUS      current
   DESCRIPTION
       " "
   ::= { opmen99810bGVRPStatisticsEntry 1 }

opmen99810bGVRPStatisticsJoinTxCnt OBJECT-TYPE
   SYNTAX      Counter32
   MAX-ACCESS  read-only
   STATUS      current
   DESCRIPTION
       ""
   ::= { opmen99810bGVRPStatisticsEntry 2 }

opmen99810bGVRPStatisticsLeaveTxCnt OBJECT-TYPE
   SYNTAX      Counter32
   MAX-ACCESS  read-only
   STATUS      current
   DESCRIPTION
       ""
   ::= { opmen99810bGVRPStatisticsEntry 3 }


opmen99810bMirroring                                             OBJECT IDENTIFIER ::= { opmen99810bConfiguration 6 }

opmen99810bPortToMirrorOn OBJECT-TYPE
   SYNTAX      Integer32(0..10)
   MAX-ACCESS  read-write
   STATUS      current
   DESCRIPTION
       "default: 0
        0: disable,
        range : 1 - port number. "
   ::= { opmen99810bMirroring 1 }

opmen99810bMirrorTable OBJECT-TYPE
   SYNTAX      SEQUENCE OF Opmen99810bMirrorEntry
   MAX-ACCESS  not-accessible
   STATUS      current
   DESCRIPTION
       " "
   ::= { opmen99810bMirroring 2 }

opmen99810bMirrorEntry OBJECT-TYPE
   SYNTAX      Opmen99810bMirrorEntry
   MAX-ACCESS  not-accessible
   STATUS      current
   DESCRIPTION
       ""
   INDEX    { opmen99810bMirrorPort  }
   ::= { opmen99810bMirrorTable 1 }

Opmen99810bMirrorEntry ::= SEQUENCE {
   opmen99810bMirrorPort		Integer32,
   opmen99810bMirrorMode		INTEGER
}

opmen99810bMirrorPort OBJECT-TYPE
   SYNTAX      Integer32(1..4095)
   MAX-ACCESS  not-accessible
   STATUS      current
   DESCRIPTION
       " "
   ::= { opmen99810bMirrorEntry 1 }

opmen99810bMirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { opmen99810bMirrorEntry 2 }

opmen99810bTrapEventSeverity                                             OBJECT IDENTIFIER ::= { opmen99810bConfiguration 7 }

opmen99810bTrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 1 }

opmen99810bTrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { opmen99810bTrapEventSeverity 2 }

opmen99810bTrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 3 }

opmen99810bTrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { opmen99810bTrapEventSeverity 4 }

opmen99810bTrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { opmen99810bTrapEventSeverity 5 }

opmen99810bTrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 6 }

opmen99810bTrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 7 }

opmen99810bTrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 8 }

opmen99810bTrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 9 }

opmen99810bTrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { opmen99810bTrapEventSeverity 10 }

opmen99810bTrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 11 }

opmen99810bTrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 12 }

opmen99810bTrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 13 }

opmen99810bTrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 14 }

opmen99810bTrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { opmen99810bTrapEventSeverity 15 }

opmen99810bTrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 16 }

opmen99810bTrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 17 }

opmen99810bTrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 18 }

opmen99810bTrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { opmen99810bTrapEventSeverity 20 }

opmen99810bTrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { opmen99810bTrapEventSeverity 21 }

opmen99810bSMTP                                             OBJECT IDENTIFIER ::= { opmen99810bConfiguration 8 }

opmen99810bSMTPMailServer OBJECT-TYPE
   SYNTAX      DisplayString
   MAX-ACCESS  read-write
   STATUS      current
   DESCRIPTION
       " Up to 47 characters describing email server. "
   ::= { opmen99810bSMTP 1 }

opmen99810bSMTPUserName OBJECT-TYPE
   SYNTAX      DisplayString
   MAX-ACCESS  read-write
   STATUS      current
   DESCRIPTION
       " Up to 47 characters describing user name. "
   ::= { opmen99810bSMTP 2 }

opmen99810bSMTPPassword OBJECT-TYPE
   SYNTAX      DisplayString
   MAX-ACCESS  read-write
   STATUS      current
   DESCRIPTION
       " Up to 47 characters describing password. "
   ::= { opmen99810bSMTP 3 }

opmen99810bSMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { opmen99810bSMTP 4 }

opmen99810bSMTPSender OBJECT-TYPE
   SYNTAX      DisplayString
   MAX-ACCESS  read-write
   STATUS      current
   DESCRIPTION
       " Up to 47 characters describing sender. "
   ::= { opmen99810bSMTP 5 }

opmen99810bSMTPReturnPath OBJECT-TYPE
   SYNTAX      DisplayString
   MAX-ACCESS  read-write
   STATUS      current
   DESCRIPTION
       " Up to 47 characters describing return path. "
   ::= { opmen99810bSMTP 6 }

opmen99810bSMTPPort OBJECT-TYPE
   SYNTAX       Integer32(1..65535)
   MAX-ACCESS  read-write
   STATUS      current
   DESCRIPTION
       "get/set smtp port, default: 25"
   ::= { opmen99810bSMTP 7 }

opmen99810bSMTPEmailAddress1 OBJECT-TYPE
   SYNTAX      DisplayString
   MAX-ACCESS  read-write
   STATUS      current
   DESCRIPTION
       " Up to 47 characters describing mail address. "
   ::= { opmen99810bSMTP 8 }

opmen99810bSMTPEmailAddress2 OBJECT-TYPE
   SYNTAX      DisplayString
   MAX-ACCESS  read-write
   STATUS      current
   DESCRIPTION
       " Up to 47 characters describing mail address. "
   ::= { opmen99810bSMTP 9 }

opmen99810bSMTPEmailAddress3 OBJECT-TYPE
   SYNTAX      DisplayString
   MAX-ACCESS  read-write
   STATUS      current
   DESCRIPTION
       " Up to 47 characters describing mail address. "
   ::= { opmen99810bSMTP 10 }

opmen99810bSMTPEmailAddress4 OBJECT-TYPE
   SYNTAX      DisplayString
   MAX-ACCESS  read-write
   STATUS      current
   DESCRIPTION
       " Up to 47 characters describing mail address. "
   ::= { opmen99810bSMTP 11 }

opmen99810bSMTPEmailAddress5 OBJECT-TYPE
   SYNTAX      DisplayString
   MAX-ACCESS  read-write
   STATUS      current
   DESCRIPTION
       " Up to 47 characters describing mail address. "
   ::= { opmen99810bSMTP 12 }

opmen99810bSMTPEmailAddress6 OBJECT-TYPE
   SYNTAX      DisplayString
   MAX-ACCESS  read-write
   STATUS      current
   DESCRIPTION
       " Up to 47 characters describing mail address. "
   ::= { opmen99810bSMTP 13 }


opmen99810bACL                                                   OBJECT IDENTIFIER ::= { opmen99810bConfiguration 9 }

opmen99810bACLPortsConfTable OBJECT-TYPE
   SYNTAX      SEQUENCE OF Opmen99810bACLPortsConfEntry
   MAX-ACCESS  not-accessible
   STATUS      current
   DESCRIPTION
       " "
   ::= { opmen99810bACL 1 }

opmen99810bACLPortsConfEntry OBJECT-TYPE
   SYNTAX      Opmen99810bACLPortsConfEntry
   MAX-ACCESS  not-accessible
   STATUS      current
   DESCRIPTION
       ""
   INDEX    { opmen99810bACLPortsConfPort  }
   ::= { opmen99810bACLPortsConfTable 1 }

Opmen99810bACLPortsConfEntry ::= SEQUENCE {
   opmen99810bACLPortsConfPort               Integer32,
   opmen99810bACLPortsConfPolicyID           Integer32,
   opmen99810bACLPortsConfAction             INTEGER,
   opmen99810bACLPortsConfRateLimiterID      Integer32,
   opmen99810bACLPortsConfPortRedirect       Integer32,
   opmen99810bACLPortsConfMirror             INTEGER,
   opmen99810bACLPortsConfLogging            INTEGER,
   opmen99810bACLPortsConfShutdown           INTEGER,
   opmen99810bACLPortsConfState              INTEGER,
   opmen99810bACLPortsConfCounter            Counter32
}

opmen99810bACLPortsConfPort OBJECT-TYPE
   SYNTAX      Integer32 (1..4095)
   MAX-ACCESS  not-accessible
   STATUS      current
   DESCRIPTION
       " "
   ::= { opmen99810bACLPortsConfEntry 1 }

opmen99810bACLPortsConfPolicyID OBJECT-TYPE
   SYNTAX      Integer32 (0..255)
   MAX-ACCESS  read-write
   STATUS      current
   DESCRIPTION
       "default: 0, range : 0 - 255 "
   ::= { opmen99810bACLPortsConfEntry 2 }

opmen99810bACLPortsConfAction OBJECT-TYPE
   SYNTAX      INTEGER { deny(0), permit(1) }
   MAX-ACCESS  read-write
   STATUS      current
   DESCRIPTION
       "default: 1,
        0: Deny
        1: Permit"
   ::= { opmen99810bACLPortsConfEntry 3 }

opmen99810bACLPortsConfRateLimiterID OBJECT-TYPE
   SYNTAX      Integer32 (0..12)
   MAX-ACCESS  read-write
   STATUS      current
   DESCRIPTION
       "default: 0,
        0: Disable
        range : 0 - 12 "
   ::= { opmen99810bACLPortsConfEntry 4 }

opmen99810bACLPortsConfPortRedirect OBJECT-TYPE
   SYNTAX      Integer32 (0..4095)
   MAX-ACCESS  read-write
   STATUS      current
   DESCRIPTION
       "default: 0
        0: Disable
        range : 0 - end port number "
   ::= { opmen99810bACLPortsConfEntry 5 }

opmen99810bACLPortsConfMirror OBJECT-TYPE
   SYNTAX      INTEGER { disable(0), enable(1) }
   MAX-ACCESS  read-write
   STATUS      current
   DESCRIPTION
       "default: 0
        0: Disable
        1: Enable "
   ::= { opmen99810bACLPortsConfEntry 6 }

opmen99810bACLPortsConfLogging OBJECT-TYPE
   SYNTAX      INTEGER { disable(0), enable(1) }
   MAX-ACCESS  read-write
   STATUS      current
   DESCRIPTION
       "default: 0
        0: Disable
        1: Enable "
   ::= { opmen99810bACLPortsConfEntry 7 }

opmen99810bACLPortsConfShutdown OBJECT-TYPE
   SYNTAX      INTEGER { disable(0), enable(1) }
   MAX-ACCESS  read-write
   STATUS      current
   DESCRIPTION
       "default: 0
        0: Disable
        1: Enable "
   ::= { opmen99810bACLPortsConfEntry 8 }

opmen99810bACLPortsConfState OBJECT-TYPE
   SYNTAX      INTEGER { disable(0), enable(1) }
   MAX-ACCESS  read-write
   STATUS      current
   DESCRIPTION
       "default: 1
        0: Disable
        1: Enable "
   ::= { opmen99810bACLPortsConfEntry 9 }

opmen99810bACLPortsConfCounter OBJECT-TYPE
   SYNTAX      Counter32
   MAX-ACCESS  read-only
   STATUS      current
   DESCRIPTION
       "Counts the number of frames that match this ACE. "
   ::= { opmen99810bACLPortsConfEntry 10 }


opmen99810bACLRateLimiterTable OBJECT-TYPE
   SYNTAX      SEQUENCE OF Opmen99810bACLRateLimiterEntry
   MAX-ACCESS  not-accessible
   STATUS      current
   DESCRIPTION
       " "
   ::= { opmen99810bACL 2 }

opmen99810bACLRateLimiterEntry OBJECT-TYPE
   SYNTAX      Opmen99810bACLRateLimiterEntry
   MAX-ACCESS  not-accessible
   STATUS      current
   DESCRIPTION
       ""
   INDEX    { opmen99810bACLRateLimiterID  }
   ::= { opmen99810bACLRateLimiterTable 1 }

Opmen99810bACLRateLimiterEntry ::= SEQUENCE {
   opmen99810bACLRateLimiterID       Integer32,
   opmen99810bACLRateLimiterUnit     INTEGER,
   opmen99810bACLRateLimiterRate     Integer32
}

opmen99810bACLRateLimiterID OBJECT-TYPE
   SYNTAX      Integer32 (1..12)
   MAX-ACCESS  not-accessible
   STATUS      current
   DESCRIPTION
       " Rate Limiter ID.
         range : 1-12 "
   ::= { opmen99810bACLRateLimiterEntry 1 }

opmen99810bACLRateLimiterUnit OBJECT-TYPE
   SYNTAX      INTEGER { pps(0), kbps(1) }
   MAX-ACCESS  read-write
   STATUS      current
   DESCRIPTION
       "default: 0,
        0: pps
        1: kbps"
   ::= { opmen99810bACLRateLimiterEntry 2 }

opmen99810bACLRateLimiterRate OBJECT-TYPE
   SYNTAX      Integer32(0..3276700)
   MAX-ACCESS  read-write
   STATUS      current
   DESCRIPTION
       "default: 1,
        range : <0-3276700> pps
                <0-10000> kbps"
   ::= { opmen99810bACLRateLimiterEntry 3 }


opmen99810bACLACE                                          OBJECT IDENTIFIER ::= { opmen99810bACL 3 }

opmen99810bACLACECreate OBJECT-TYPE
   SYNTAX       INTEGER { none(0), create(1) }
   MAX-ACCESS   read-write
   STATUS       current
   DESCRIPTION
       "default: 0
        0 : None  (read only)
        1 : Create an ACE entry"
   ::= { opmen99810bACLACE 1 }

opmen99810bACLACETable OBJECT-TYPE
   SYNTAX      SEQUENCE OF Opmen99810bACLACEEntry
   MAX-ACCESS  not-accessible
   STATUS      current
   DESCRIPTION
       " Create ACL ACE entry. "
   ::= { opmen99810bACLACE 2 }

opmen99810bACLACEEntry OBJECT-TYPE
   SYNTAX      Opmen99810bACLACEEntry
   MAX-ACCESS  not-accessible
   STATUS      current
   DESCRIPTION
       ""
   INDEX    { opmen99810bACLACEIndex  }
   ::= { opmen99810bACLACETable 1 }

Opmen99810bACLACEEntry ::= SEQUENCE {
   opmen99810bACLACEIndex                Integer32,
   opmen99810bACLACEID                   Integer32,
   opmen99810bACLACENextID               Integer32,
   opmen99810bACLACEIngressPort          DisplayString,
   opmen99810bACLACEPortPolicyNumber     Integer32,

   opmen99810bACLACEPortPolicyBitmask    Integer32,
   opmen99810bACLACEFrameType            INTEGER,
   opmen99810bACLACEAction               INTEGER,
   opmen99810bACLACEDenyPortRedirect     DisplayString,
   opmen99810bACLACELogging              INTEGER,

   opmen99810bACLACEMirror               INTEGER,
   opmen99810bACLACERateLimiter          Integer32,
   opmen99810bACLACEShutdown             INTEGER,
   opmen99810bACLACEVLAN8021QTagged      INTEGER,
   opmen99810bACLACEVLANTagPriority      Integer32,

   opmen99810bACLACEVLANVID              Integer32,
   opmen99810bACLACEEtherType            Integer32,
   opmen99810bACLACESMAC                 DisplayString,
   opmen99810bACLACEDMACType             INTEGER,
   opmen99810bACLACEDMAC                 DisplayString,

   opmen99810bACLACEArpOpcode            INTEGER,
   opmen99810bACLACEArpFlagsRequestReply INTEGER,
   opmen99810bACLACEArpFlagsArpSmac      INTEGER,
   opmen99810bACLACEArpFlagsRarpDmac     INTEGER,
   opmen99810bACLACEArpFlagsLength       INTEGER,

   opmen99810bACLACEArpFlagsIp           INTEGER,
   opmen99810bACLACEArpFlagsEthernet     INTEGER,
   opmen99810bACLACESIPType              INTEGER,
   opmen99810bACLACESIPIPAddress         IpAddress,
   opmen99810bACLACESIPNetworkPrefix     Integer32,

   opmen99810bACLACEDIPType              INTEGER,
   opmen99810bACLACEDIPIPAddress         IpAddress,
   opmen99810bACLACEDIPNetworkPrefix     Integer32,

   opmen99810bACLACEIPProtocol           Integer32,
   opmen99810bACLACEIPFlagsTTL           INTEGER,
   opmen99810bACLACEIPFlagsOptions       INTEGER,
   opmen99810bACLACEIPFlagsFragment      INTEGER,
   opmen99810bACLACEICMPType             Integer32,

   opmen99810bACLACEICMPCode             Integer32,
   opmen99810bACLACESourcePortMin        Integer32,
   opmen99810bACLACESourcePortMax        Integer32,
   opmen99810bACLACEDestPortMin          Integer32,
   opmen99810bACLACEDestPortMax          Integer32,

   opmen99810bACLACETCPFlagsFin          INTEGER,
   opmen99810bACLACETCPFlagsSyn          INTEGER,
   opmen99810bACLACETCPFlagsRst          INTEGER,
   opmen99810bACLACETCPFlagsPsh          INTEGER,
   opmen99810bACLACETCPFlagsAck          INTEGER,

   opmen99810bACLACETCPFlagsUrg          INTEGER,

   opmen99810bACLACERowStatus            INTEGER
}

opmen99810bACLACEIndex OBJECT-TYPE
   SYNTAX      Integer32(1..256)
   MAX-ACCESS  not-accessible
   STATUS      current
   DESCRIPTION
       " "
   ::= { opmen99810bACLACEEntry 1 }

opmen99810bACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { opmen99810bACLACEEntry 2 }

opmen99810bACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { opmen99810bACLACEEntry 3 }

opmen99810bACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { opmen99810bACLACEEntry 4 }

opmen99810bACLACEPortPolicyNumber OBJECT-TYPE
   SYNTAX      Integer32(0..255)
   MAX-ACCESS  read-write
   STATUS      current
   DESCRIPTION
       " policy value.
         range : 0 - 255. "
   ::= { opmen99810bACLACEEntry 5 }

opmen99810bACLACEPortPolicyBitmask OBJECT-TYPE
   SYNTAX      Integer32(0..255)
   MAX-ACCESS  read-write
   STATUS      current
   DESCRIPTION
       " policy bitmask.
         range : 0 - 255(0xff). "
   ::= { opmen99810bACLACEEntry 6 }

opmen99810bACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { opmen99810bACLACEEntry 7 }

opmen99810bACLACEAction OBJECT-TYPE
   SYNTAX      INTEGER { deny(0), permit(1) }
   MAX-ACCESS  read-write
   STATUS      current
   DESCRIPTION
       "default: 1,
        0: Deny
        1: Permit"
   ::= { opmen99810bACLACEEntry 8 }

opmen99810bACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { opmen99810bACLACEEntry 9 }

opmen99810bACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { opmen99810bACLACEEntry 10 }

opmen99810bACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { opmen99810bACLACEEntry 11 }

opmen99810bACLACERateLimiter OBJECT-TYPE
   SYNTAX      Integer32(0..12)
   MAX-ACCESS  read-write
   STATUS      current
   DESCRIPTION
       "default: 0,
        0: Disable
        range : 0 - 12 "
   ::= { opmen99810bACLACEEntry 12 }

opmen99810bACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { opmen99810bACLACEEntry 13 }

opmen99810bACLACEVLAN8021QTagged OBJECT-TYPE
   SYNTAX      INTEGER { disable(0), enable(1), any(2) }
   MAX-ACCESS  read-write
   STATUS      current
   DESCRIPTION
       "Specify whether frames can hit the action according to the 802.1Q tagged.
        default: 2,
        0: disable - Untagged frame only.
        1: enable - Tagged frame only.
        2: Any - Any value is allowed. "
   ::= { opmen99810bACLACEEntry 14 }

opmen99810bACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { opmen99810bACLACEEntry 15 }

opmen99810bACLACEVLANVID OBJECT-TYPE
   SYNTAX      Integer32(0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { opmen99810bACLACEEntry 16 }

opmen99810bACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { opmen99810bACLACEEntry 17 }

opmen99810bACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { opmen99810bACLACEEntry 18 }

opmen99810bACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { opmen99810bACLACEEntry 19 }

opmen99810bACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { opmen99810bACLACEEntry 20 }

opmen99810bACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { opmen99810bACLACEEntry 21 }

opmen99810bACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { opmen99810bACLACEEntry 22 }

opmen99810bACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { opmen99810bACLACEEntry 23 }

opmen99810bACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { opmen99810bACLACEEntry 24 }

opmen99810bACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { opmen99810bACLACEEntry 25 }

opmen99810bACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { opmen99810bACLACEEntry 26 }

opmen99810bACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { opmen99810bACLACEEntry 27 }

opmen99810bACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { opmen99810bACLACEEntry 28 }

opmen99810bACLACESIPIPAddress OBJECT-TYPE
   SYNTAX      IpAddress
   MAX-ACCESS  read-write
   STATUS      current
   DESCRIPTION
       "A frame that hits this ACE matches this source IP address value."
   ::= { opmen99810bACLACEEntry 29 }

opmen99810bACLACESIPNetworkPrefix OBJECT-TYPE
   SYNTAX      Integer32(0..32)
   MAX-ACCESS  read-write
   STATUS      current
   DESCRIPTION
       "Network prefix.
        default: 32,
        0: No data.
        range : 1 - 32"
   ::= { opmen99810bACLACEEntry 30 }


opmen99810bACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { opmen99810bACLACEEntry 32 }

opmen99810bACLACEDIPIPAddress OBJECT-TYPE
   SYNTAX      IpAddress
   MAX-ACCESS  read-write
   STATUS      current
   DESCRIPTION
       "A frame that hits this ACE matches this destination IP address value."
   ::= { opmen99810bACLACEEntry 33 }

opmen99810bACLACEDIPNetworkPrefix OBJECT-TYPE
   SYNTAX      Integer32(0..32)
   MAX-ACCESS  read-write
   STATUS      current
   DESCRIPTION
       "Network prefix.
        default: 32,
        0: No data.
        range : 1 - 32"
   ::= { opmen99810bACLACEEntry 34 }


opmen99810bACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { opmen99810bACLACEEntry 36 }

opmen99810bACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { opmen99810bACLACEEntry 37 }

opmen99810bACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { opmen99810bACLACEEntry 38 }

opmen99810bACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { opmen99810bACLACEEntry 39 }

opmen99810bACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { opmen99810bACLACEEntry 40 }

opmen99810bACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { opmen99810bACLACEEntry 41 }

opmen99810bACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { opmen99810bACLACEEntry 42 }

opmen99810bACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { opmen99810bACLACEEntry 43 }

opmen99810bACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { opmen99810bACLACEEntry 44 }

opmen99810bACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { opmen99810bACLACEEntry 45 }

opmen99810bACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { opmen99810bACLACEEntry 46 }

opmen99810bACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { opmen99810bACLACEEntry 47 }

opmen99810bACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { opmen99810bACLACEEntry 48 }

opmen99810bACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { opmen99810bACLACEEntry 49 }

opmen99810bACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { opmen99810bACLACEEntry 50 }

opmen99810bACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { opmen99810bACLACEEntry 51 }

opmen99810bACLACERowStatus OBJECT-TYPE
   SYNTAX      INTEGER { active(1), notInservice(2), destroy(4), undo(5) }
   MAX-ACCESS  read-write
   STATUS      current
   DESCRIPTION
       " 1: active
         2: notInservice
         4: destroy
         5: undo"
   ::= { opmen99810bACLACEEntry 66 }


opmen99810bACLACEClear OBJECT-TYPE
   SYNTAX       INTEGER { noAction(0), clear(1) }
   MAX-ACCESS   read-write
   STATUS       current
   DESCRIPTION
       "default: 0
        0 : No action
        1 : Clear all ACL counters."
   ::= { opmen99810bACLACE 3 }

opmen99810bACLACEMoveACEID OBJECT-TYPE
   SYNTAX       Integer32(0..256)
   MAX-ACCESS   read-write
   STATUS       current
   DESCRIPTION
       "Move ACE,
        default: 0
        ACE ID must be exist.
        range : 1 - 256."
   ::= { opmen99810bACLACE 4 }

opmen99810bACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { opmen99810bACLACE 5 }

opmen99810bACLACEStatusTable OBJECT-TYPE
   SYNTAX      SEQUENCE OF Opmen99810bACLACEStatusEntry
   MAX-ACCESS  not-accessible
   STATUS      current
   DESCRIPTION
       " ACL ACE Status entry. "
   ::= { opmen99810bACLACE 6 }

opmen99810bACLACEStatusEntry OBJECT-TYPE
   SYNTAX      Opmen99810bACLACEStatusEntry
   MAX-ACCESS  not-accessible
   STATUS      current
   DESCRIPTION
       ""
   INDEX    { opmen99810bACLACEStatusIndex  }
   ::= { opmen99810bACLACEStatusTable 1 }

Opmen99810bACLACEStatusEntry ::= SEQUENCE {
   opmen99810bACLACEStatusIndex          Integer32,
   opmen99810bACLACEStatusUser           DisplayString,
   opmen99810bACLACEStatusID             Integer32,
   opmen99810bACLACEStatusIngressPort    DisplayString,
   opmen99810bACLACEStatusFrameType      DisplayString,
   opmen99810bACLACEStatusAction         DisplayString,
   opmen99810bACLACEStatusRateLimiter    DisplayString,
   opmen99810bACLACEStatusPortCopy       DisplayString,
   opmen99810bACLACEStatusMirror         DisplayString,
   opmen99810bACLACEStatusCPU            DisplayString,
   opmen99810bACLACEStatusCounter        Counter32,
   opmen99810bACLACEStatusConflict       DisplayString
}

opmen99810bACLACEStatusIndex OBJECT-TYPE
   SYNTAX      Integer32(1..256)
   MAX-ACCESS  not-accessible
   STATUS      current
   DESCRIPTION
       " "
   ::= { opmen99810bACLACEStatusEntry 1 }

opmen99810bACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { opmen99810bACLACEStatusEntry 2 }

opmen99810bACLACEStatusID OBJECT-TYPE
   SYNTAX      Integer32(1..256)
   MAX-ACCESS  read-only
   STATUS      current
   DESCRIPTION
       " ACE ID.
         range : 1 - 256. "
   ::= { opmen99810bACLACEStatusEntry 3 }

opmen99810bACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { opmen99810bACLACEStatusEntry 4 }

opmen99810bACLACEStatusFrameType OBJECT-TYPE
   SYNTAX      DisplayString
   MAX-ACCESS  read-only
   STATUS      current
   DESCRIPTION
       " Indicates the frame type of the ACE. "
   ::= { opmen99810bACLACEStatusEntry 5 }

opmen99810bACLACEStatusAction OBJECT-TYPE
   SYNTAX      DisplayString
   MAX-ACCESS  read-only
   STATUS      current
   DESCRIPTION
       " Indicates the forwarding action of the ACE. "
   ::= { opmen99810bACLACEStatusEntry 6 }

opmen99810bACLACEStatusRateLimiter OBJECT-TYPE
   SYNTAX      DisplayString
   MAX-ACCESS  read-only
   STATUS      current
   DESCRIPTION
       " Indicates the rate limiter number of the ACE. "
   ::= { opmen99810bACLACEStatusEntry 7 }

opmen99810bACLACEStatusPortCopy OBJECT-TYPE
   SYNTAX      DisplayString
   MAX-ACCESS  read-only
   STATUS      current
   DESCRIPTION
       " Indicates the port redirect operation of the ACE. Frames matching the ACE are redirected to the port number. "
   ::= { opmen99810bACLACEStatusEntry 8 }

opmen99810bACLACEStatusMirror OBJECT-TYPE
   SYNTAX      DisplayString
   MAX-ACCESS  read-only
   STATUS      current
   DESCRIPTION
       " Specify the mirror operation of this port. "
   ::= { opmen99810bACLACEStatusEntry 9 }

opmen99810bACLACEStatusCPU OBJECT-TYPE
   SYNTAX      DisplayString
   MAX-ACCESS  read-only
   STATUS      current
   DESCRIPTION
       " Forward packet that matched the specific ACE to CPU. "
   ::= { opmen99810bACLACEStatusEntry 10 }

opmen99810bACLACEStatusCounter OBJECT-TYPE
   SYNTAX      Counter32
   MAX-ACCESS  read-only
   STATUS      current
   DESCRIPTION
       " The counter indicates the number of times the ACE was hit by a frame. "
   ::= { opmen99810bACLACEStatusEntry 11 }

opmen99810bACLACEStatusConflict OBJECT-TYPE
   SYNTAX      DisplayString
   MAX-ACCESS  read-only
   STATUS      current
   DESCRIPTION
       " Indicates the hardware status of the specific ACE. The specific ACE is not applied to the hardware due to hardware limitations. "
   ::= { opmen99810bACLACEStatusEntry 12 }

opmen99810bBroadcastStormProtection                                                  OBJECT IDENTIFIER ::= { opmen99810bConfiguration 11 }

opmen99810bBroadcastStormProtectionConfigurationTable OBJECT-TYPE
   SYNTAX      SEQUENCE OF Opmen99810bBroadcastStormProtectionConfigurationEntry
   MAX-ACCESS  not-accessible
   STATUS      current
   DESCRIPTION
       " Show Broadcast Storm Protection configurations. "
   ::= { opmen99810bBroadcastStormProtection 1 }

opmen99810bBroadcastStormProtectionConfigurationEntry OBJECT-TYPE
   SYNTAX      Opmen99810bBroadcastStormProtectionConfigurationEntry
   MAX-ACCESS  not-accessible
   STATUS      current
   DESCRIPTION
       ""
   INDEX    { opmen99810bBroadcastStormProtectionConfPort  }
   ::= { opmen99810bBroadcastStormProtectionConfigurationTable 1 }

Opmen99810bBroadcastStormProtectionConfigurationEntry ::= SEQUENCE {
   opmen99810bBroadcastStormProtectionConfPort	INTEGER,
   opmen99810bBroadcastStormProtectionConfMode	INTEGER,
   opmen99810bBroadcastStormProtectionConfAction	INTEGER,
   opmen99810bBroadcastStormProtectionConfPPS		INTEGER,
   opmen99810bBroadcastStormProtectionConfTimer	INTEGER,
   opmen99810bBroadcastStormProtectionConfstatus	DisplayString
}

opmen99810bBroadcastStormProtectionConfPort OBJECT-TYPE
   SYNTAX      INTEGER (1..4095)
   MAX-ACCESS  not-accessible
   STATUS      current
   DESCRIPTION
       " port, range : 1 - port number. "
   ::= { opmen99810bBroadcastStormProtectionConfigurationEntry 1 }

opmen99810bBroadcastStormProtectionConfMode OBJECT-TYPE
   SYNTAX      INTEGER { disable(0), enable(1)}
   MAX-ACCESS  read-write
   STATUS      current
   DESCRIPTION
       " Configure broadcast storm protection port mode.
         0: disable,
         1: enable
         default: disable. "
   ::= { opmen99810bBroadcastStormProtectionConfigurationEntry 2 }

opmen99810bBroadcastStormProtectionConfAction OBJECT-TYPE
   SYNTAX      INTEGER (0..2)
   MAX-ACCESS  read-write
   STATUS      current
   DESCRIPTION
       " Configure broadcast storm protection port action.
         0: Shutdown port,
         1: Shutdown port and Log,
         2: Log Only,
         default: Shutdown port. "
   ::= { opmen99810bBroadcastStormProtectionConfigurationEntry 3 }

opmen99810bBroadcastStormProtectionConfPPS OBJECT-TYPE
   SYNTAX      INTEGER (0..1000000)
   MAX-ACCESS  read-write
   STATUS      current
   DESCRIPTION
       " Configure broadcast storm protection pps.
         default: 0. "
   ::= { opmen99810bBroadcastStormProtectionConfigurationEntry 4 }

opmen99810bBroadcastStormProtectionConfTimer OBJECT-TYPE
   SYNTAX      INTEGER (0..65535)
   MAX-ACCESS  read-write
   STATUS      current
   DESCRIPTION
       "Configure broadcast storm protection timer(seconds)
        default: 300(seconds). "
   ::= { opmen99810bBroadcastStormProtectionConfigurationEntry 5 }

opmen99810bBroadcastStormProtectionConfstatus OBJECT-TYPE
   SYNTAX      DisplayString
   MAX-ACCESS  read-only
   STATUS      current
   DESCRIPTION
       " Show broadcast storm protection status. "
   ::= { opmen99810bBroadcastStormProtectionConfigurationEntry 6 }


opmen99810bLoopProtection                                                  OBJECT IDENTIFIER ::= { opmen99810bConfiguration 12 }

opmen99810bLoopProtectionConfig                                            OBJECT IDENTIFIER ::= { opmen99810bLoopProtection 1 }

opmen99810bLoopProtectionGlobalEnable OBJECT-TYPE
   SYNTAX      INTEGER { disable(0), enable(1) }
   MAX-ACCESS  read-write
   STATUS      current
   DESCRIPTION
       "Configure loop protection mode.
        0: disable,
        1: enable,
        default: disable. "
   ::= { opmen99810bLoopProtectionConfig 1 }

opmen99810bLoopProtectionTranmisstionTime OBJECT-TYPE
   SYNTAX      Integer32(1..10)
   MAX-ACCESS  read-write
   STATUS      current
   DESCRIPTION
       "Configure loop protection transmit interval.
        default: 5,
        range: 1-10. "
   ::= { opmen99810bLoopProtectionConfig 2 }

opmen99810bLoopProtectionShutdownTime OBJECT-TYPE
   SYNTAX      Integer32(0..604800)
   MAX-ACCESS  read-write
   STATUS      current
   DESCRIPTION
       "Configure loop protection shutdown time.
        default: 180,
        range: 0-604800. "
   ::= { opmen99810bLoopProtectionConfig 3 }

opmen99810bLoopProtectionConfigurationTable OBJECT-TYPE
   SYNTAX      SEQUENCE OF Opmen99810bLoopProtectionConfigurationEntry
   MAX-ACCESS  not-accessible
   STATUS      current
   DESCRIPTION
       " Show Loop Protection configurations. "
   ::= { opmen99810bLoopProtectionConfig 4 }

opmen99810bLoopProtectionConfigurationEntry OBJECT-TYPE
   SYNTAX      Opmen99810bLoopProtectionConfigurationEntry
   MAX-ACCESS  not-accessible
   STATUS      current
   DESCRIPTION
       ""
   INDEX    { opmen99810bLoopProtectionConfPort  }
   ::= { opmen99810bLoopProtectionConfigurationTable 1 }

Opmen99810bLoopProtectionConfigurationEntry ::= SEQUENCE {
   opmen99810bLoopProtectionConfPort	    Integer32,
   opmen99810bLoopProtectionConfEnable	INTEGER,
   opmen99810bLoopProtectionConfAction	INTEGER,
   opmen99810bLoopProtectionConfTxmode	INTEGER
}

opmen99810bLoopProtectionConfPort OBJECT-TYPE
   SYNTAX      Integer32(1..4095)
   MAX-ACCESS  not-accessible
   STATUS      current
   DESCRIPTION
       " port, range : 1 - port number. "
   ::= { opmen99810bLoopProtectionConfigurationEntry 1 }

opmen99810bLoopProtectionConfEnable OBJECT-TYPE
   SYNTAX      INTEGER { disable(0), enable(1) }
   MAX-ACCESS  read-write
   STATUS      current
   DESCRIPTION
       "Configure loop protection port mode.
        0: disable,
        1: enable,
        default: enable. "
   ::= { opmen99810bLoopProtectionConfigurationEntry 2 }

opmen99810bLoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { opmen99810bLoopProtectionConfigurationEntry 3 }

opmen99810bLoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { opmen99810bLoopProtectionConfigurationEntry 4 }

opmen99810bLoopProtectionStatusTable OBJECT-TYPE
   SYNTAX      SEQUENCE OF Opmen99810bLoopProtectionStatusEntry
   MAX-ACCESS  not-accessible
   STATUS      current
   DESCRIPTION
       " Show Loop Protection Status. "
   ::= { opmen99810bLoopProtection 2 }

opmen99810bLoopProtectionStatusEntry OBJECT-TYPE
   SYNTAX      Opmen99810bLoopProtectionStatusEntry
   MAX-ACCESS  not-accessible
   STATUS      current
   DESCRIPTION
       ""
   INDEX    { opmen99810bLoopProtectionStatusPort  }
   ::= { opmen99810bLoopProtectionStatusTable 1 }

Opmen99810bLoopProtectionStatusEntry ::= SEQUENCE {
   opmen99810bLoopProtectionStatusPort	       Integer32,
   opmen99810bLoopProtectionStatusAction	       DisplayString,
   opmen99810bLoopProtectionStatusTransmit	   DisplayString,
   opmen99810bLoopProtectionStatusLoops	       Integer32,
   opmen99810bLoopProtectionStatusStatus	       DisplayString,
   opmen99810bLoopProtectionStatusLoop	       DisplayString,
   opmen99810bLoopProtectionStatusTimeLastLoop  DisplayString
}

opmen99810bLoopProtectionStatusPort OBJECT-TYPE
   SYNTAX      Integer32(1..4095)
   MAX-ACCESS  not-accessible
   STATUS      current
   DESCRIPTION
       " port, range : 1 - port number. "
   ::= { opmen99810bLoopProtectionStatusEntry 1 }

opmen99810bLoopProtectionStatusAction OBJECT-TYPE
   SYNTAX      DisplayString
   MAX-ACCESS  read-only
   STATUS      current
   DESCRIPTION
       " The currently configured port action. "
   ::= { opmen99810bLoopProtectionStatusEntry 2 }

opmen99810bLoopProtectionStatusTransmit OBJECT-TYPE
   SYNTAX      DisplayString
   MAX-ACCESS  read-only
   STATUS      current
   DESCRIPTION
       " The currently configured port transmit mode. "
   ::= { opmen99810bLoopProtectionStatusEntry 3 }

opmen99810bLoopProtectionStatusLoops OBJECT-TYPE
   SYNTAX      Integer32(0..1000000)
   MAX-ACCESS  read-only
   STATUS      current
   DESCRIPTION
       " The number of loops detected on this port. "
   ::= { opmen99810bLoopProtectionStatusEntry 4 }

opmen99810bLoopProtectionStatusStatus OBJECT-TYPE
   SYNTAX      DisplayString
   MAX-ACCESS  read-only
   STATUS      current
   DESCRIPTION
       " The current loop protection status of the port. "
   ::= { opmen99810bLoopProtectionStatusEntry 5 }

opmen99810bLoopProtectionStatusLoop OBJECT-TYPE
   SYNTAX      DisplayString
   MAX-ACCESS  read-only
   STATUS      current
   DESCRIPTION
       " Whether a loop is currently detected on the port. "
   ::= { opmen99810bLoopProtectionStatusEntry 6 }

opmen99810bLoopProtectionStatusTimeLastLoop OBJECT-TYPE
   SYNTAX      DisplayString
   MAX-ACCESS  read-only
   STATUS      current
   DESCRIPTION
       " The time of the last loop event detected. "
   ::= { opmen99810bLoopProtectionStatusEntry 7 }

opmen99810bQos                                                             OBJECT IDENTIFIER ::= { opmen99810bConfiguration 14 }

opmen99810bQosPortClassification                                           OBJECT IDENTIFIER ::= { opmen99810bQos 1 }

opmen99810bQosPortClassificationTable OBJECT-TYPE
   SYNTAX      SEQUENCE OF Opmen99810bQosPortClassificationEntry
   MAX-ACCESS  not-accessible
   STATUS      current
   DESCRIPTION
       " QoS Ingress Port Classification . "
   ::= { opmen99810bQosPortClassification  1 }

opmen99810bQosPortClassificationEntry OBJECT-TYPE
   SYNTAX      Opmen99810bQosPortClassificationEntry
   MAX-ACCESS  not-accessible
   STATUS      current
   DESCRIPTION
       ""
   INDEX    { opmen99810bQosPortClassificationPort  }
   ::= { opmen99810bQosPortClassificationTable 1 }

Opmen99810bQosPortClassificationEntry ::= SEQUENCE {
   opmen99810bQosPortClassificationPort	        Integer32,
   opmen99810bQosPortClassificationQoSclass       Integer32,
   opmen99810bQosPortClassificationDPlevel	    Integer32,
   opmen99810bQosPortClassificationPCP	        Integer32,
   opmen99810bQosPortClassificationDEI	        INTEGER,
   opmen99810bQosPortClassificationTagClass	    INTEGER,
   opmen99810bQosPortClassificationDSCPBased    INTEGER
}

opmen99810bQosPortClassificationPort OBJECT-TYPE
   SYNTAX      Integer32(1..4095)
   MAX-ACCESS  not-accessible
   STATUS      current
   DESCRIPTION
       " port, range : 1 - port number. "
   ::= { opmen99810bQosPortClassificationEntry 1 }

opmen99810bQosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { opmen99810bQosPortClassificationEntry 2 }

opmen99810bQosPortClassificationDPlevel OBJECT-TYPE
   SYNTAX      Integer32(0|1)
   MAX-ACCESS  read-write
   STATUS      current
   DESCRIPTION
       " DP level for frames not classified in any other way.
         range: 0-1,
         default: 0. "
   ::= { opmen99810bQosPortClassificationEntry 3 }

opmen99810bQosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { opmen99810bQosPortClassificationEntry 4 }

opmen99810bQosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { opmen99810bQosPortClassificationEntry 5 }

opmen99810bQosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { opmen99810bQosPortClassificationEntry 6 }

opmen99810bQosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { opmen99810bQosPortClassificationEntry 7 }

opmen99810bQoSIngressPortTagClassificationTable OBJECT-TYPE
   SYNTAX      SEQUENCE OF Opmen99810bQoSIngressPortTagClassificationEntry
   MAX-ACCESS  not-accessible
   STATUS      current
   DESCRIPTION
       " Show QoS Ingress Port Tag Classification. "
   ::= { opmen99810bQosPortClassification 2 }

opmen99810bQoSIngressPortTagClassificationEntry OBJECT-TYPE
   SYNTAX      Opmen99810bQoSIngressPortTagClassificationEntry
   MAX-ACCESS  not-accessible
   STATUS      current
   DESCRIPTION
       ""
   INDEX    { opmen99810bQoSIngressPortTagClassificationPort, opmen99810bQoSIngressPortTagPCP, opmen99810bQoSIngressPortTagDEI  }
   ::= { opmen99810bQoSIngressPortTagClassificationTable 1 }

Opmen99810bQoSIngressPortTagClassificationEntry ::= SEQUENCE {
   opmen99810bQoSIngressPortTagClassificationPort	Integer32,
   opmen99810bQoSIngressPortTagPCP					INTEGER,
   opmen99810bQoSIngressPortTagDEI					INTEGER,
   opmen99810bQoSIngressPortTagQosClass				Integer32,
   opmen99810bQoSIngressPortTagDPLevel				Integer32
}

opmen99810bQoSIngressPortTagClassificationPort OBJECT-TYPE
   SYNTAX      Integer32(1..4095)
   MAX-ACCESS  not-accessible
   STATUS      current
   DESCRIPTION
       " port, range : 1 - port number. "
   ::= { opmen99810bQoSIngressPortTagClassificationEntry 1 }

opmen99810bQoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8,
         PCP0:1, PCP1:2...  "
   ::= { opmen99810bQoSIngressPortTagClassificationEntry 2 }

opmen99810bQoSIngressPortTagDEI OBJECT-TYPE
   SYNTAX      INTEGER { dei0(1), dei1(2) }
   MAX-ACCESS  not-accessible
   STATUS      current
   DESCRIPTION
       " range: 1-2,
         DEI0:1, DEI1:2. "
   ::= { opmen99810bQoSIngressPortTagClassificationEntry 3 }

opmen99810bQoSIngressPortTagQosClass OBJECT-TYPE
   SYNTAX      Integer32 (0..7)
   MAX-ACCESS  read-write
   STATUS      current
   DESCRIPTION
       " range: 0-7.  "
   ::= { opmen99810bQoSIngressPortTagClassificationEntry 4 }

opmen99810bQoSIngressPortTagDPLevel OBJECT-TYPE
   SYNTAX      Integer32 (0|1)
   MAX-ACCESS  read-write
   STATUS      current
   DESCRIPTION
       " range: 0-1.  "
   ::= { opmen99810bQoSIngressPortTagClassificationEntry 5 }


opmen99810bQosPortPolicingTable OBJECT-TYPE
   SYNTAX      SEQUENCE OF Opmen99810bQosPortPolicingEntry
   MAX-ACCESS  not-accessible
   STATUS      current
   DESCRIPTION
       "  configure the Policer settings for all switch ports. "
   ::= { opmen99810bQos  2 }

opmen99810bQosPortPolicingEntry OBJECT-TYPE
   SYNTAX      Opmen99810bQosPortPolicingEntry
   MAX-ACCESS  not-accessible
   STATUS      current
   DESCRIPTION
       ""
   INDEX    { opmen99810bQosPortPolicingPort  }
   ::= { opmen99810bQosPortPolicingTable 1 }

Opmen99810bQosPortPolicingEntry ::= SEQUENCE {
   opmen99810bQosPortPolicingPort	        Integer32,
   opmen99810bQosPortPolicingMode           INTEGER,
   opmen99810bQosPortPolicingRate	        Integer32,
   opmen99810bQosPortPolicingUnit	        INTEGER,
   opmen99810bQosPortPolicingFlowControl	INTEGER
}

opmen99810bQosPortPolicingPort OBJECT-TYPE
   SYNTAX      Integer32 (1..4095)
   MAX-ACCESS  not-accessible
   STATUS      current
   DESCRIPTION
       " port, range : 1 - port number. "
   ::= { opmen99810bQosPortPolicingEntry 1 }

opmen99810bQosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { opmen99810bQosPortPolicingEntry 2 }

opmen99810bQosPortPolicingRate OBJECT-TYPE
   SYNTAX      Integer32(100..10000000)
   MAX-ACCESS  read-write
   STATUS      current
   DESCRIPTION
       " Controls the rate for the policer.
         range: 100-10000000(kbps/fps),
         default: 500(kbps). "
   ::= { opmen99810bQosPortPolicingEntry 3 }

opmen99810bQosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { opmen99810bQosPortPolicingEntry 4 }

opmen99810bQosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { opmen99810bQosPortPolicingEntry 5 }

opmen99810bQosPortScheduler                                           OBJECT IDENTIFIER ::= { opmen99810bQos 3 }

opmen99810bQosPortSchedulerModeTable OBJECT-TYPE
   SYNTAX      SEQUENCE OF Opmen99810bQosPortSchedulerModeEntry
   MAX-ACCESS  not-accessible
   STATUS      current
   DESCRIPTION
       " configure the basic QoS Port Scheduler Mode settings for all switch ports. "
   ::= { opmen99810bQosPortScheduler  1 }

opmen99810bQosPortSchedulerModeEntry OBJECT-TYPE
   SYNTAX      Opmen99810bQosPortSchedulerModeEntry
   MAX-ACCESS  not-accessible
   STATUS      current
   DESCRIPTION
       ""
   INDEX    { opmen99810bQosSchedulerModePort  }
   ::= { opmen99810bQosPortSchedulerModeTable 1 }

Opmen99810bQosPortSchedulerModeEntry ::= SEQUENCE {
   opmen99810bQosSchedulerModePort	                Integer32,
   opmen99810bQosSchedulerMode                        INTEGER,
   opmen99810bQosSchedulerShaper	                    INTEGER,
   opmen99810bQosSchedulerShaperRate	                Integer32
}

opmen99810bQosSchedulerModePort OBJECT-TYPE
   SYNTAX      Integer32 (1..4095)
   MAX-ACCESS  not-accessible
   STATUS      current
   DESCRIPTION
       " port, range : 1 - port number. "
   ::= { opmen99810bQosPortSchedulerModeEntry 1 }

opmen99810bQosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { opmen99810bQosPortSchedulerModeEntry 2 }

opmen99810bQosSchedulerShaper OBJECT-TYPE
   SYNTAX      INTEGER { disable(0), enable(1) }
   MAX-ACCESS  read-write
   STATUS      current
   DESCRIPTION
       " Controls whether the port shaper is enabled
         0: Disable
         1: Enable.
         default: disable. "
   ::= { opmen99810bQosPortSchedulerModeEntry 3 }

opmen99810bQosSchedulerShaperRate OBJECT-TYPE
   SYNTAX      Integer32(100..1000000)
   MAX-ACCESS  read-write
   STATUS      current
   DESCRIPTION
       " Controls the rate for the port shaper.
         range: 100-1000000
         default: 500 kbps. "
   ::= { opmen99810bQosPortSchedulerModeEntry 4 }

opmen99810bQosPortSchedulerTable OBJECT-TYPE
   SYNTAX      SEQUENCE OF Opmen99810bQosPortSchedulerEntry
   MAX-ACCESS  not-accessible
   STATUS      current
   DESCRIPTION
       " Show Qos Port Scheduler. "
   ::= { opmen99810bQosPortScheduler 2 }

opmen99810bQosPortSchedulerEntry OBJECT-TYPE
   SYNTAX      Opmen99810bQosPortSchedulerEntry
   MAX-ACCESS  not-accessible
   STATUS      current
   DESCRIPTION
       ""
   INDEX    { opmen99810bQosSchedulerPort, opmen99810bQosSchedulerPortQueue}
   ::= { opmen99810bQosPortSchedulerTable 1 }

Opmen99810bQosPortSchedulerEntry ::= SEQUENCE {
   opmen99810bQosSchedulerPort						Integer32,
   opmen99810bQosSchedulerPortQueue					INTEGER,
   opmen99810bQosSchedulerPortQueueShaper				INTEGER,
   opmen99810bQosSchedulerPortQueueShaperRate			Integer32,
   opmen99810bQosSchedulerPortQueueShaperExcess		INTEGER,
   opmen99810bQosSchedulerPortQueueSchedulerWeight	Integer32,
   opmen99810bQosSchedulerPortQueueSchedulerPercent	DisplayString
}

opmen99810bQosSchedulerPort OBJECT-TYPE
   SYNTAX      Integer32 (1..4095)
   MAX-ACCESS  not-accessible
   STATUS      current
   DESCRIPTION
       " port, range : 1 - port number. "
   ::= { opmen99810bQosPortSchedulerEntry 1 }

opmen99810bQosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { opmen99810bQosPortSchedulerEntry 2 }

opmen99810bQosSchedulerPortQueueShaper OBJECT-TYPE
   SYNTAX      INTEGER { disable(0), enable(1) }
   MAX-ACCESS  read-write
   STATUS      current
   DESCRIPTION
       " 0: disable  1:enable,
         default: 0.  "
   ::= { opmen99810bQosPortSchedulerEntry 3 }

opmen99810bQosSchedulerPortQueueShaperRate OBJECT-TYPE
   SYNTAX      Integer32(100..1000000)
   MAX-ACCESS  read-write
   STATUS      current
   DESCRIPTION
       " range: 100..1000000 kbps.  "
   ::= { opmen99810bQosPortSchedulerEntry 4 }

opmen99810bQosSchedulerPortQueueShaperExcess OBJECT-TYPE
   SYNTAX      INTEGER { disable(0), enable(1) }
   MAX-ACCESS  read-write
   STATUS      current
   DESCRIPTION
       " 0: disable  1:enable,
         default: 0.  "
   ::= { opmen99810bQosPortSchedulerEntry 5 }

opmen99810bQosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { opmen99810bQosPortSchedulerEntry 6 }

opmen99810bQosSchedulerPortQueueSchedulerPercent OBJECT-TYPE
   SYNTAX      DisplayString
   MAX-ACCESS  read-only
   STATUS      current
   DESCRIPTION
       " Only use in Q0 - Q5. Q6 & Q7 show empty "
   ::= { opmen99810bQosPortSchedulerEntry 7 }

opmen99810bQosPortEgressTagRemarking                                           OBJECT IDENTIFIER ::= { opmen99810bQos 4 }

opmen99810bQosPortEgressTagRemarkingTable OBJECT-TYPE
   SYNTAX      SEQUENCE OF Opmen99810bQosPortEgressTagRemarkingEntry
   MAX-ACCESS  not-accessible
   STATUS      current
   DESCRIPTION
       " configure the basic QoS Port Egress Tag Remark Configuration settings for all switch ports. "
   ::= { opmen99810bQosPortEgressTagRemarking  1 }

opmen99810bQosPortEgressTagRemarkingEntry OBJECT-TYPE
   SYNTAX      Opmen99810bQosPortEgressTagRemarkingEntry
   MAX-ACCESS  not-accessible
   STATUS      current
   DESCRIPTION
       ""
   INDEX    { opmen99810bQosEgressTagRemarkingPort  }
   ::= { opmen99810bQosPortEgressTagRemarkingTable 1 }

Opmen99810bQosPortEgressTagRemarkingEntry ::= SEQUENCE {
   opmen99810bQosEgressTagRemarkingPort	                Integer32,
   opmen99810bQosEgressTagRemarkingMode	                INTEGER
}

opmen99810bQosEgressTagRemarkingPort OBJECT-TYPE
   SYNTAX      Integer32 (1..4095)
   MAX-ACCESS  not-accessible
   STATUS      current
   DESCRIPTION
       " port, range : 1 - port number. "
   ::= { opmen99810bQosPortEgressTagRemarkingEntry 1 }

opmen99810bQosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { opmen99810bQosPortEgressTagRemarkingEntry 2 }


opmen99810bQosPortEgressTagRemarkingDefTable OBJECT-TYPE
   SYNTAX      SEQUENCE OF Opmen99810bQosPortEgressTagRemarkingDefEntry
   MAX-ACCESS  not-accessible
   STATUS      current
   DESCRIPTION
       " configure the basic QoS Port Egress Tag Remark Configuration settings for all switch ports. "
   ::= { opmen99810bQosPortEgressTagRemarking  2 }

opmen99810bQosPortEgressTagRemarkingDefEntry OBJECT-TYPE
   SYNTAX      Opmen99810bQosPortEgressTagRemarkingDefEntry
   MAX-ACCESS  not-accessible
   STATUS      current
   DESCRIPTION
       ""
   INDEX    { opmen99810bQosEgressTagRemarkingDefPort  }
   ::= { opmen99810bQosPortEgressTagRemarkingDefTable 1 }

Opmen99810bQosPortEgressTagRemarkingDefEntry ::= SEQUENCE {
   opmen99810bQosEgressTagRemarkingDefPort	            Integer32,
   opmen99810bQosEgressTagRemarkingDefPCP	                Integer32,
   opmen99810bQosEgressTagRemarkingDefDEI	                INTEGER
}

opmen99810bQosEgressTagRemarkingDefPort OBJECT-TYPE
   SYNTAX      Integer32(1..4095)
   MAX-ACCESS  not-accessible
   STATUS      current
   DESCRIPTION
       " port, range : 1 - port number. "
   ::= { opmen99810bQosPortEgressTagRemarkingDefEntry 1 }

opmen99810bQosEgressTagRemarkingDefPCP OBJECT-TYPE
   SYNTAX      Integer32(0..7)
   MAX-ACCESS  read-write
   STATUS      current
   DESCRIPTION
       " Controls the default PCP
       Range : 0-7"
   ::= { opmen99810bQosPortEgressTagRemarkingDefEntry 2 }

opmen99810bQosEgressTagRemarkingDefDEI OBJECT-TYPE
   SYNTAX      INTEGER { disable(0), enable(1) }
   MAX-ACCESS  read-write
   STATUS      current
   DESCRIPTION
       " controls the DEI
       Range 0-1"
   ::= { opmen99810bQosPortEgressTagRemarkingDefEntry 3 }

opmen99810bQosPortEgressTagRemarkingMapTable OBJECT-TYPE
   SYNTAX      SEQUENCE OF Opmen99810bQosPortEgressTagRemarkingMapEntry
   MAX-ACCESS  not-accessible
   STATUS      current
   DESCRIPTION
       " Show Qos Port Egress Tag Remarking Map. "
   ::= { opmen99810bQosPortEgressTagRemarking 4 }

opmen99810bQosPortEgressTagRemarkingMapEntry OBJECT-TYPE
   SYNTAX      Opmen99810bQosPortEgressTagRemarkingMapEntry
   MAX-ACCESS  not-accessible
   STATUS      current
   DESCRIPTION
       ""
   INDEX    { opmen99810bQosPortEgressTagRemarkingMapPort, opmen99810bQosTagRemarkingQoSClass, opmen99810bQosTagRemarkingDPLevel  }
   ::= { opmen99810bQosPortEgressTagRemarkingMapTable 1 }

Opmen99810bQosPortEgressTagRemarkingMapEntry ::= SEQUENCE {
   opmen99810bQosPortEgressTagRemarkingMapPort	Integer32,
   opmen99810bQosTagRemarkingQoSClass			INTEGER,
   opmen99810bQosTagRemarkingDPLevel				INTEGER,
   opmen99810bQosTagRemarkingPCP					Integer32,
   opmen99810bQosTagRemarkingDEI					INTEGER
}

opmen99810bQosPortEgressTagRemarkingMapPort OBJECT-TYPE
   SYNTAX      Integer32 (1..4095)
   MAX-ACCESS  not-accessible
   STATUS      current
   DESCRIPTION
       " port, range : 1 - port number. "
   ::= { opmen99810bQosPortEgressTagRemarkingMapEntry 1 }

opmen99810bQosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8,
         QoS Class0: 1, QoS Class1: 2...  "
   ::= { opmen99810bQosPortEgressTagRemarkingMapEntry 2 }

opmen99810bQosTagRemarkingDPLevel OBJECT-TYPE
   SYNTAX      INTEGER { level0(1), level1(2) }
   MAX-ACCESS  not-accessible
   STATUS      current
   DESCRIPTION
       " range: 1-2,
         DP Level0: 1, DP Level1: 2. "
   ::= { opmen99810bQosPortEgressTagRemarkingMapEntry 3 }

opmen99810bQosTagRemarkingPCP OBJECT-TYPE
   SYNTAX      Integer32 (0..7)
   MAX-ACCESS  read-write
   STATUS      current
   DESCRIPTION
       " range: 0-7.  "
   ::= { opmen99810bQosPortEgressTagRemarkingMapEntry 4 }

opmen99810bQosTagRemarkingDEI OBJECT-TYPE
   SYNTAX      INTEGER (0|1)
   MAX-ACCESS  read-write
   STATUS      current
   DESCRIPTION
       " range: 0-1.  "
   ::= { opmen99810bQosPortEgressTagRemarkingMapEntry 5 }


opmen99810bQosPortDSCPTable OBJECT-TYPE
   SYNTAX      SEQUENCE OF Opmen99810bQosPortDSCPEntry
   MAX-ACCESS  not-accessible
   STATUS      current
   DESCRIPTION
       " configure the basic QoS Port DSCP Configuration settings for all switch ports. "
   ::= { opmen99810bQos  5 }

opmen99810bQosPortDSCPEntry OBJECT-TYPE
   SYNTAX      Opmen99810bQosPortDSCPEntry
   MAX-ACCESS  not-accessible
   STATUS      current
   DESCRIPTION
       ""
   INDEX    { opmen99810bQosPortDSCPPort  }
   ::= { opmen99810bQosPortDSCPTable 1 }

Opmen99810bQosPortDSCPEntry ::= SEQUENCE {
   opmen99810bQosPortDSCPPort	                Integer32,
   opmen99810bQosPortDSCPIngressTranslate       INTEGER,
   opmen99810bQosPortDSCPIngressClassify	    INTEGER,
   opmen99810bQosPortDSCPEgressRewrite	        INTEGER
}

opmen99810bQosPortDSCPPort OBJECT-TYPE
   SYNTAX      Integer32 (1..4095)
   MAX-ACCESS  not-accessible
   STATUS      current
   DESCRIPTION
       " port, range : 1 - port number. "
   ::= { opmen99810bQosPortDSCPEntry 1 }

opmen99810bQosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { opmen99810bQosPortDSCPEntry 2 }

opmen99810bQosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { opmen99810bQosPortDSCPEntry 3 }

opmen99810bQosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { opmen99810bQosPortDSCPEntry 4 }


opmen99810bQosDSCPTable OBJECT-TYPE
   SYNTAX      SEQUENCE OF Opmen99810bQosDSCPEntry
   MAX-ACCESS  not-accessible
   STATUS      current
   DESCRIPTION
       " configure the basic QoS DSCP based QoS Ingress Classification settings for all switches. "
   ::= { opmen99810bQos  6 }

opmen99810bQosDSCPEntry OBJECT-TYPE
   SYNTAX      Opmen99810bQosDSCPEntry
   MAX-ACCESS  not-accessible
   STATUS      current
   DESCRIPTION
       ""
   INDEX    { opmen99810bQosDSCPList  }
   ::= { opmen99810bQosDSCPTable 1 }

Opmen99810bQosDSCPEntry ::= SEQUENCE {
   opmen99810bQosDSCPList       Integer32,
   opmen99810bQosDSCP           DisplayString,
   opmen99810bQosDSCPTrust      INTEGER,
   opmen99810bQosDSCPQosClass	  Integer32,
   opmen99810bQosDSCPDPL	      INTEGER
}

opmen99810bQosDSCPList OBJECT-TYPE
   SYNTAX      Integer32(1..64)
   MAX-ACCESS  not-accessible
   STATUS      current
   DESCRIPTION
      " DSCP mapping table index(1-64). "
   ::= { opmen99810bQosDSCPEntry 1 }

opmen99810bQosDSCP OBJECT-TYPE
   SYNTAX      DisplayString
   MAX-ACCESS  read-only
   STATUS      current
   DESCRIPTION
      "Maximum number of supported DSCP values are 64."
   ::= { opmen99810bQosDSCPEntry 2 }

opmen99810bQosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { opmen99810bQosDSCPEntry 3 }

opmen99810bQosDSCPQosClass OBJECT-TYPE
   SYNTAX      Integer32(0..7)
   MAX-ACCESS  read-write
   STATUS      current
   DESCRIPTION
      " QoS class.
        range: 0-7,
        default: 0. "
   ::= { opmen99810bQosDSCPEntry 4 }

opmen99810bQosDSCPDPL OBJECT-TYPE
   SYNTAX      INTEGER(0|1)
   MAX-ACCESS  read-write
   STATUS      current
   DESCRIPTION
      " Drop Precedence Level.
        range: 0-1,
        default: disable. "
   ::= { opmen99810bQosDSCPEntry 5 }

opmen99810bQosDSCPTranslationTable OBJECT-TYPE
   SYNTAX      SEQUENCE OF Opmen99810bQosDSCPTranslationEntry
   MAX-ACCESS  not-accessible
   STATUS      current
   DESCRIPTION
       "  configure the basic QoS DSCP Translation settings for all switches. "
   ::= { opmen99810bQos  7 }

opmen99810bQosDSCPTranslationEntry OBJECT-TYPE
   SYNTAX      Opmen99810bQosDSCPTranslationEntry
   MAX-ACCESS  not-accessible
   STATUS      current
   DESCRIPTION
       ""
   INDEX    { opmen99810bQosDSCPTranslationList  }
   ::= { opmen99810bQosDSCPTranslationTable 1 }

Opmen99810bQosDSCPTranslationEntry ::= SEQUENCE {
   opmen99810bQosDSCPTranslationList                 Integer32,
   opmen99810bQosDSCPTranslationDSCPBasedId          DisplayString,
   opmen99810bQosDSCPTranslationIngressTranslate     Integer32,
   opmen99810bQosDSCPTranslationIngressClassify      INTEGER,
   opmen99810bQosDSCPTranslationEgressRemapDP0       Integer32,
   opmen99810bQosDSCPTranslationEgressRemapDP1       Integer32
}

opmen99810bQosDSCPTranslationList OBJECT-TYPE
   SYNTAX      Integer32(1..64)
   MAX-ACCESS  not-accessible
   STATUS      current
   DESCRIPTION
      " DSCP translation table index(1-64). "
   ::= { opmen99810bQosDSCPTranslationEntry 1 }

opmen99810bQosDSCPTranslationDSCPBasedId OBJECT-TYPE
   SYNTAX      DisplayString
   MAX-ACCESS  read-write
   STATUS      current
   DESCRIPTION
      " Configure global ingress DSCP translation table. "
   ::= { opmen99810bQosDSCPTranslationEntry 2 }

opmen99810bQosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { opmen99810bQosDSCPTranslationEntry 3 }

opmen99810bQosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { opmen99810bQosDSCPTranslationEntry 4 }

opmen99810bQosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { opmen99810bQosDSCPTranslationEntry 5 }

opmen99810bQosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { opmen99810bQosDSCPTranslationEntry 6 }


opmen99810bQosDSCPClassificationTable OBJECT-TYPE
   SYNTAX      SEQUENCE OF Opmen99810bQosDSCPClassificationEntry
   MAX-ACCESS  not-accessible
   STATUS      current
   DESCRIPTION
       "   configure the mapping of QoS class  to DSCP value. "
   ::= { opmen99810bQos  8 }

opmen99810bQosDSCPClassificationEntry OBJECT-TYPE
   SYNTAX      Opmen99810bQosDSCPClassificationEntry
   MAX-ACCESS  not-accessible
   STATUS      current
   DESCRIPTION
       ""
   INDEX    { opmen99810bQosDSCPClassificationQoSClass, opmen99810bQosDSCPClassificationDPL }
   ::= { opmen99810bQosDSCPClassificationTable 1 }

Opmen99810bQosDSCPClassificationEntry ::= SEQUENCE {
   opmen99810bQosDSCPClassificationQoSClass		INTEGER,
   opmen99810bQosDSCPClassificationDPL			INTEGER,
   opmen99810bQosDSCPClassificationDSCP			Integer32
}

opmen99810bQosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { opmen99810bQosDSCPClassificationEntry 1 }

opmen99810bQosDSCPClassificationDPL OBJECT-TYPE
   SYNTAX      INTEGER(1|2)
   MAX-ACCESS  not-accessible
   STATUS      current
   DESCRIPTION
      " DPL. Index 1~2 mean DPL 0~1."
   ::= { opmen99810bQosDSCPClassificationEntry 2 }

opmen99810bQosDSCPClassificationDSCP OBJECT-TYPE
   SYNTAX      Integer32(0..63)
   MAX-ACCESS  read-write
   STATUS      current
   DESCRIPTION
      " Select the classified DSCP value.
        range: 0-63,
        default: 0. "
   ::= { opmen99810bQosDSCPClassificationEntry 3 }

opmen99810bQosControlList                                         OBJECT IDENTIFIER ::= { opmen99810bQos 9 }

opmen99810bQosQceCreate OBJECT-TYPE
   SYNTAX       INTEGER { none(0), create(1) }
   MAX-ACCESS   read-write
   STATUS       current
   DESCRIPTION
       "default: 0
        0 : None  (read only)
        1 : Create an Qos entry"
   ::= { opmen99810bQosControlList 1 }

opmen99810bQosQceTable OBJECT-TYPE
   SYNTAX      SEQUENCE OF Opmen99810bQosQceEntry
   MAX-ACCESS  not-accessible
   STATUS      current
   DESCRIPTION
       " Create Qos QCE entry. "
   ::= { opmen99810bQosControlList 2 }

opmen99810bQosQceEntry OBJECT-TYPE
   SYNTAX      Opmen99810bQosQceEntry
   MAX-ACCESS  not-accessible
   STATUS      current
   DESCRIPTION
       ""
   INDEX    { opmen99810bQosQceIndex  }
   ::= { opmen99810bQosQceTable 1 }

Opmen99810bQosQceEntry ::= SEQUENCE {
   opmen99810bQosQceIndex                Integer32,
   opmen99810bQosQceID                   Integer32,
   opmen99810bQosQceNextID               Integer32,
   opmen99810bQosQcePortMembers          DisplayString,

   opmen99810bQosQceTag                  DisplayString,
   opmen99810bQosQceVID                  DisplayString,
   opmen99810bQosPCP                     DisplayString,
   opmen99810bQosDEI                     DisplayString,
   opmen99810bQosSMAC                    DisplayString,
   opmen99810bQosDMACType                DisplayString,
   opmen99810bQosFrameType               INTEGER,

   opmen99810bQosMacEtherType            DisplayString,

   opmen99810bQosLLCSSAPAddr             DisplayString,
   opmen99810bQosLLCDSAPAddr             DisplayString,
   opmen99810bQosLLCControl              DisplayString,

   opmen99810bQosSNAPPID                 DisplayString,

   opmen99810bQosIpv4Protocol            DisplayString,
   opmen99810bQosIpv4ProtocolValue       Integer32,
   opmen99810bQosIpv4ProtocolUDPSport    DisplayString,
   opmen99810bQosIpv4ProtocolUDPDport    DisplayString,
   opmen99810bQosIpv4ProtocolTCPSport    DisplayString,
   opmen99810bQosIpv4ProtocolTCPDport    DisplayString,
   opmen99810bQosIpv4SourceIp            DisplayString,
   opmen99810bQosIpv4SourceMask          DisplayString,
   opmen99810bQosIpv4IPFragment          INTEGER,
   opmen99810bQosIpv4DSCP                DisplayString,


   opmen99810bQosIpv6Protocol            DisplayString,
   opmen99810bQosIpv6ProtocolValue       Integer32,
   opmen99810bQosIpv6ProtocolUDPSport    DisplayString,
   opmen99810bQosIpv6ProtocolUDPDport    DisplayString,
   opmen99810bQosIpv6ProtocolTCPSport    DisplayString,
   opmen99810bQosIpv6ProtocolTCPDport    DisplayString,
   opmen99810bQosIpv6SourceIp            DisplayString,
   opmen99810bQosIpv6SourceMask          DisplayString,
   opmen99810bQosIpv6DSCP                DisplayString,

   opmen99810bQosActionClass             Integer32,
   opmen99810bQosActionDPL               INTEGER,
   opmen99810bQosActionDSCP              Integer32,
   opmen99810bQosQceRowStatus            INTEGER
}

opmen99810bQosQceIndex OBJECT-TYPE
   SYNTAX      Integer32(1..256)
   MAX-ACCESS  not-accessible
   STATUS      current
   DESCRIPTION
       " "
   ::= { opmen99810bQosQceEntry 1 }

opmen99810bQosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { opmen99810bQosQceEntry 2 }

opmen99810bQosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { opmen99810bQosQceEntry 3 }

opmen99810bQosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { opmen99810bQosQceEntry 4 }

opmen99810bQosQceTag OBJECT-TYPE
   SYNTAX      DisplayString
   MAX-ACCESS  read-write
   STATUS      current
   DESCRIPTION
       " Value of Tag field can be 'Any', 'Untag' or 'Tag'. "
   ::= { opmen99810bQosQceEntry 5 }

opmen99810bQosQceVID OBJECT-TYPE
   SYNTAX      DisplayString
   MAX-ACCESS  read-write
   STATUS      current
   DESCRIPTION
       " Valid value of VLAN ID can be any value in 'Specific 1~4094' or 'range 1-4094' or 'Any'. "
   ::= { opmen99810bQosQceEntry 6 }

opmen99810bQosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { opmen99810bQosQceEntry 7 }

opmen99810bQosDEI OBJECT-TYPE
   SYNTAX      DisplayString
   MAX-ACCESS  read-write
   STATUS      current
   DESCRIPTION
       " Drop Eligible Indicator: Valid value of DEI can be any of values between 0, 1 or 'Any'. "
   ::= { opmen99810bQosQceEntry 8 }

opmen99810bQosSMAC  OBJECT-TYPE
   SYNTAX      DisplayString
   MAX-ACCESS  read-write
   STATUS      current
   DESCRIPTION
       "  Source MAC address: 24 MS bits OUI(00-00-00 ~ FF-FF-FF) or 'Any'. "
   ::= { opmen99810bQosQceEntry 9 }

opmen99810bQosDMACType OBJECT-TYPE
   SYNTAX      DisplayString
   MAX-ACCESS  read-write
   STATUS      current
   DESCRIPTION
       " Destination MAC type: possible values are 'UC'(unicast), 'MC'(multicast), 'BC'(broadcast) or 'Any'. "
   ::= { opmen99810bQosQceEntry 10 }

opmen99810bQosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { opmen99810bQosQceEntry 11 }

opmen99810bQosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { opmen99810bQosQceEntry 12 }

opmen99810bQosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { opmen99810bQosQceEntry 13 }

opmen99810bQosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { opmen99810bQosQceEntry 14 }

opmen99810bQosLLCControl OBJECT-TYPE
   SYNTAX      DisplayString
   MAX-ACCESS  read-write
   STATUS      current
   DESCRIPTION
       " Valid Control field can vary from 0x00 to 0xFF or 'Any',
         range: 00-FF,
         default: Any. "
   ::= { opmen99810bQosQceEntry 15 }

opmen99810bQosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { opmen99810bQosQceEntry 16 }

opmen99810bQosIpv4Protocol OBJECT-TYPE
   SYNTAX      DisplayString
   MAX-ACCESS  read-write
   STATUS      current
   DESCRIPTION
       " IP protocol number: (Other, TCP or UDP) or 'Any'. "
   ::= { opmen99810bQosQceEntry 17 }

opmen99810bQosIpv4ProtocolValue  OBJECT-TYPE
   SYNTAX      Integer32(0..255)
   MAX-ACCESS  read-write
   STATUS      current
   DESCRIPTION
       " Ipv4 Protocol is Other.
         range: 0-255
         default: 0. "
   ::= { opmen99810bQosQceEntry 18 }

opmen99810bQosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { opmen99810bQosQceEntry 19 }

opmen99810bQosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { opmen99810bQosQceEntry 20 }

opmen99810bQosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { opmen99810bQosQceEntry 21 }

opmen99810bQosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { opmen99810bQosQceEntry 22 }

opmen99810bQosIpv4SourceIp OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223."
   ::= { opmen99810bQosQceEntry 23 }

opmen99810bQosIpv4SourceMask OBJECT-TYPE
   SYNTAX      DisplayString
   MAX-ACCESS  read-write
   STATUS      current
   DESCRIPTION
       " Specific Source IP address in mask format or value 0.0.0.0 is 'Any'. "
   ::= { opmen99810bQosQceEntry 24 }

opmen99810bQosIpv4IPFragment OBJECT-TYPE
   SYNTAX      INTEGER { any(0), no(1), yes(2) }
   MAX-ACCESS  read-write
   STATUS      current
   DESCRIPTION
       " IPv4 frame fragmented option:
         2: yes,
         1: no,
         0: any. "
   ::= { opmen99810bQosQceEntry 25 }

opmen99810bQosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { opmen99810bQosQceEntry 26 }

opmen99810bQosIpv6Protocol OBJECT-TYPE
   SYNTAX      DisplayString
   MAX-ACCESS  read-write
   STATUS      current
   DESCRIPTION
       " IP protocol number: (Other, TCP or UDP) or 'Any'. "
   ::= { opmen99810bQosQceEntry 27 }

opmen99810bQosIpv6ProtocolValue OBJECT-TYPE
   SYNTAX      Integer32(0..255)
   MAX-ACCESS  read-write
   STATUS      current
   DESCRIPTION
       " when IPv6 protocol is Other ,
         range: 0-255. "
   ::= { opmen99810bQosQceEntry 28 }

opmen99810bQosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { opmen99810bQosQceEntry 29 }

opmen99810bQosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { opmen99810bQosQceEntry 30 }

opmen99810bQosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { opmen99810bQosQceEntry 31 }


opmen99810bQosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { opmen99810bQosQceEntry 32 }

opmen99810bQosIpv6SourceIp OBJECT-TYPE
   SYNTAX      DisplayString
   MAX-ACCESS  read-write
   STATUS      current
   DESCRIPTION
       " IPv6 source address: (a.b.c.d) or value 0.0.0.0 is 'Any', 32 LS bits. "
   ::= { opmen99810bQosQceEntry 33 }

opmen99810bQosIpv6SourceMask OBJECT-TYPE
   SYNTAX      DisplayString
   MAX-ACCESS  read-write
   STATUS      current
   DESCRIPTION
       " IPv6 mask address: (a.b.c.d) or value 0.0.0.0 is 'Any', 32 LS bits. "
   ::= { opmen99810bQosQceEntry 34 }

opmen99810bQosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { opmen99810bQosQceEntry 35 }

opmen99810bQosActionClass  OBJECT-TYPE
   SYNTAX      Integer32(0..8)
   MAX-ACCESS  read-write
   STATUS      current
   DESCRIPTION
       " QoS class: (0-7) or 8: Default."
   ::= { opmen99810bQosQceEntry 36 }

opmen99810bQosActionDPL OBJECT-TYPE
   SYNTAX      INTEGER (0..4)
   MAX-ACCESS  read-write
   STATUS      current
   DESCRIPTION
       " DP Valid Drop Precedence Level can be (0-3) or 4: Default. "
   ::= { opmen99810bQosQceEntry 37 }

opmen99810bQosActionDSCP OBJECT-TYPE
   SYNTAX      Integer32(0..64)
   MAX-ACCESS  read-write
   STATUS      current
   DESCRIPTION
       " Valid DSCP value can be (0-63, BE, CS1-CS7, EF or AF11-AF43) or 64: Default. "
   ::= { opmen99810bQosQceEntry 38 }

opmen99810bQosQceRowStatus OBJECT-TYPE
   SYNTAX      INTEGER { active(1), notInservice(2), destroy(4) }
   MAX-ACCESS  read-write
   STATUS      current
   DESCRIPTION
       "  1: active2: notInservice 4: destroy"
   ::= { opmen99810bQosQceEntry 39 }

opmen99810bQosQceMoveID OBJECT-TYPE
   SYNTAX       Integer32(0..256)
   MAX-ACCESS   read-write
   STATUS       current
   DESCRIPTION
       " Move Qos,
         default: 0
         Qos ID must be exist.
         range : 0 - 256."
   ::= { opmen99810bQosControlList 3 }

opmen99810bQosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { opmen99810bQosControlList 4 }


opmen99810bQosQCLStatusTable OBJECT-TYPE
   SYNTAX      SEQUENCE OF Opmen99810bQosQCLStatusEntry
   MAX-ACCESS  not-accessible
   STATUS      current
   DESCRIPTION
       "  configure the basic QoS DSCP Translation settings for all switches. "
   ::= { opmen99810bQos  10 }

opmen99810bQosQCLStatusEntry OBJECT-TYPE
   SYNTAX      Opmen99810bQosQCLStatusEntry
   MAX-ACCESS  not-accessible
   STATUS      current
   DESCRIPTION
       ""
   INDEX    { opmen99810bQosQCLStatusList  }
   ::= { opmen99810bQosQCLStatusTable 1 }

Opmen99810bQosQCLStatusEntry ::= SEQUENCE {
   opmen99810bQosQCLStatusList               Integer32,
   opmen99810bQosQCLStatusUser               DisplayString,
   opmen99810bQosQCLStatusQCEId              DisplayString,
   opmen99810bQosQCLStatusFrameType          DisplayString,
   opmen99810bQosQCLStatusPortlist           DisplayString,
   opmen99810bQosQCLStatusActionClass	       DisplayString,
   opmen99810bQosQCLStatusActionDPL	       DisplayString,
   opmen99810bQosQCLStatusActionDSCP	       DisplayString,
   opmen99810bQosQCLStatusActionConflict     DisplayString
}

opmen99810bQosQCLStatusList OBJECT-TYPE
   SYNTAX      Integer32(1..4095)
   MAX-ACCESS  not-accessible
   STATUS      current
   DESCRIPTION
       " QCL table index. "
   ::= { opmen99810bQosQCLStatusEntry 1}

opmen99810bQosQCLStatusUser OBJECT-TYPE
   SYNTAX      DisplayString
   MAX-ACCESS  read-only
   STATUS      current
   DESCRIPTION
       " Indicates the QCL user. "
   ::= { opmen99810bQosQCLStatusEntry 2 }

opmen99810bQosQCLStatusQCEId OBJECT-TYPE
   SYNTAX      DisplayString
   MAX-ACCESS  read-only
   STATUS      current
   DESCRIPTION
      " Indicates the index of QCE. "
   ::= { opmen99810bQosQCLStatusEntry 3}

opmen99810bQosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { opmen99810bQosQCLStatusEntry 4}

opmen99810bQosQCLStatusPortlist OBJECT-TYPE
   SYNTAX      DisplayString
   MAX-ACCESS  read-only
   STATUS      current
   DESCRIPTION
       " Indicates the list of ports configured with the QCE. "
   ::= { opmen99810bQosQCLStatusEntry 5}

opmen99810bQosQCLStatusActionClass OBJECT-TYPE
   SYNTAX      DisplayString
   MAX-ACCESS  read-only
   STATUS      current
   DESCRIPTION
       " Classified QoS class; if a frame matches the QCE it will be put in the
       queue. "
   ::= { opmen99810bQosQCLStatusEntry 6}

opmen99810bQosQCLStatusActionDPL OBJECT-TYPE
   SYNTAX      DisplayString
   MAX-ACCESS  read-only
   STATUS      current
   DESCRIPTION
       " Drop Precedence Level; if a frame matches the QCE then DP level will
       set to value displayed under DPL column."
   ::= { opmen99810bQosQCLStatusEntry 7}

opmen99810bQosQCLStatusActionDSCP OBJECT-TYPE
   SYNTAX      DisplayString
   MAX-ACCESS  read-only
   STATUS      current
   DESCRIPTION
       " If a frame matches the QCE then DSCP will be classified with the value
       displayed under DSCP column."
   ::= { opmen99810bQosQCLStatusEntry 8}

opmen99810bQosQCLStatusActionConflict OBJECT-TYPE
   SYNTAX      DisplayString
   MAX-ACCESS  read-only
   STATUS      current
   DESCRIPTION
       " If a frame matches the QCE then DSCP will be classified with the value
        displayed under DSCP column. "
   ::= { opmen99810bQosQCLStatusEntry 9}


opmen99810bQosStormControl                                           OBJECT IDENTIFIER ::= { opmen99810bQos 11 }

opmen99810bQoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { opmen99810bQosStormControl 2 }

opmen99810bQoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { opmen99810bQosStormControl 3 }

opmen99810bQoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { opmen99810bQosStormControl 4 }

opmen99810bQoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { opmen99810bQosStormControl 5 }

opmen99810bQoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { opmen99810bQosStormControl 6 }

opmen99810bQoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { opmen99810bQosStormControl 7 }

opmen99810bVlan                                                           OBJECT IDENTIFIER ::= { opmen99810bConfiguration 15 }

opmen99810bVlanPorts                                                      OBJECT IDENTIFIER ::= { opmen99810bVlan 1 }

opmen99810bVlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { opmen99810bVlanPorts 1 }

opmen99810bVlanPortsTable OBJECT-TYPE
   SYNTAX      SEQUENCE OF Opmen99810bVlanPortsEntry
   MAX-ACCESS  not-accessible
   STATUS      current
   DESCRIPTION
       " Configure Vlan ports Configuration mode. "
   ::= { opmen99810bVlanPorts 2 }

opmen99810bVlanPortsEntry OBJECT-TYPE
   SYNTAX      Opmen99810bVlanPortsEntry
   MAX-ACCESS  not-accessible
   STATUS      current
   DESCRIPTION
       ""
   INDEX    { opmen99810bVlanPortsPort  }
   ::= { opmen99810bVlanPortsTable 1 }

Opmen99810bVlanPortsEntry ::= SEQUENCE {
   opmen99810bVlanPortsPort	         Integer32,
   opmen99810bVlanPortsPVID     Integer32,
   opmen99810bVlanPortsFrameType      INTEGER,
   opmen99810bVlanPortsIngressFilter  INTEGER,
   opmen99810bVlanPortsEgressRule     INTEGER,
   opmen99810bVlanPortsPortType       INTEGER
}

opmen99810bVlanPortsPort OBJECT-TYPE
   SYNTAX      Integer32(1..4094)
   MAX-ACCESS  not-accessible
   STATUS      current
   DESCRIPTION
       " port, range : 1 - port number. "
   ::= { opmen99810bVlanPortsEntry 1 }

opmen99810bVlanPortsPVID OBJECT-TYPE
   SYNTAX      Integer32(1..4094)
   MAX-ACCESS  read-write
   STATUS      current
   DESCRIPTION
       "Configure PVID.
        range: 1-4094,
        default: 1. "
   ::= { opmen99810bVlanPortsEntry 2 }

opmen99810bVlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { opmen99810bVlanPortsEntry 3 }

opmen99810bVlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { opmen99810bVlanPortsEntry 4 }

opmen99810bVlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { opmen99810bVlanPortsEntry 5 }

opmen99810bVlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { opmen99810bVlanPortsEntry 6 }

----------------------------------------------------------------------------------------------------------------------------
opmen99810bSecurity                                              OBJECT IDENTIFIER ::= { opmen99810bProductId 3 }

opmen99810bIPSourceGuard                                         OBJECT IDENTIFIER ::= { opmen99810bSecurity 1 }

opmen99810bIPSourceGuardConf                                     OBJECT IDENTIFIER ::= { opmen99810bIPSourceGuard 1 }

opmen99810bIPSourceGuardMode OBJECT-TYPE
   SYNTAX      INTEGER { disable(0), enable(1) }
   MAX-ACCESS  read-write
   STATUS      current
   DESCRIPTION
       " default:  0
        0: disable
        1: enable"
   ::= { opmen99810bIPSourceGuardConf 1 }

opmen99810bIPSourceGuardPortConfigTable OBJECT-TYPE
   SYNTAX      SEQUENCE OF Opmen99810bIPSourceGuardPortConfigEntry
   MAX-ACCESS  not-accessible
   STATUS      current
   DESCRIPTION
       " "
   ::= { opmen99810bIPSourceGuardConf 2 }

opmen99810bIPSourceGuardPortConfigEntry OBJECT-TYPE
   SYNTAX      Opmen99810bIPSourceGuardPortConfigEntry
   MAX-ACCESS  not-accessible
   STATUS      current
   DESCRIPTION
       ""
   INDEX    { opmen99810bIPSourceGuardPortConfigPort  }
   ::= { opmen99810bIPSourceGuardPortConfigTable 1 }

Opmen99810bIPSourceGuardPortConfigEntry ::= SEQUENCE {
   opmen99810bIPSourceGuardPortConfigPort               Integer32,
   opmen99810bIPSourceGuardPortConfigMode               INTEGER,
   opmen99810bIPSourceGuardPortMaxDynamicClients        Integer32
}

opmen99810bIPSourceGuardPortConfigPort OBJECT-TYPE
   SYNTAX      Integer32(1..4095)
   MAX-ACCESS  not-accessible
   STATUS      current
   DESCRIPTION
       " "
   ::= { opmen99810bIPSourceGuardPortConfigEntry 1 }

opmen99810bIPSourceGuardPortConfigMode OBJECT-TYPE
   SYNTAX      INTEGER { disable(0), enable(1) }
   MAX-ACCESS  read-write
   STATUS      current
   DESCRIPTION
       "default: 0
       0:disable
       1:enable "
   ::= { opmen99810bIPSourceGuardPortConfigEntry 2 }

opmen99810bIPSourceGuardPortMaxDynamicClients OBJECT-TYPE
   SYNTAX      Integer32(0..2|99)
   MAX-ACCESS  read-write
   STATUS      current
   DESCRIPTION
       "default: 99
       0~2: Max Dynamic clients
       99:Unlimited "
   ::= { opmen99810bIPSourceGuardPortConfigEntry 3 }


opmen99810bIPSourceGuardStatic                                OBJECT IDENTIFIER ::= { opmen99810bIPSourceGuard 2 }

opmen99810bIPSourceGuardStaticCreate OBJECT-TYPE
   SYNTAX       INTEGER { none(0), create(1) }
   MAX-ACCESS   read-write
   STATUS       current
   DESCRIPTION
       "default: 0
        0 : None  (read only)
        1 : Create a IP Source Guard"
   ::= { opmen99810bIPSourceGuardStatic 1 }

opmen99810bIPSourceGuardStaticTable OBJECT-TYPE
   SYNTAX      SEQUENCE OF Opmen99810bIPSourceGuardStaticEntry
   MAX-ACCESS  not-accessible
   STATUS      current
   DESCRIPTION
       " "
   ::= { opmen99810bIPSourceGuardStatic 2 }

opmen99810bIPSourceGuardStaticEntry OBJECT-TYPE
   SYNTAX      Opmen99810bIPSourceGuardStaticEntry
   MAX-ACCESS  not-accessible
   STATUS      current
   DESCRIPTION
       ""
   INDEX    { opmen99810bIPSourceGuardStaticIndex  }
   ::= { opmen99810bIPSourceGuardStaticTable 1 }

Opmen99810bIPSourceGuardStaticEntry ::= SEQUENCE {
   opmen99810bIPSourceGuardStaticIndex         Integer32,
   opmen99810bIPSourceGuardStaticPort          Integer32,
   opmen99810bIPSourceGuardStaticVLANId        Integer32,
   opmen99810bIPSourceGuardStaticIPAddress     IpAddress,
   opmen99810bIPSourceGuardStaticMACAddress    MacAddress,
   opmen99810bIPSourceGuardStaticRowStatus     INTEGER
}

opmen99810bIPSourceGuardStaticIndex OBJECT-TYPE
   SYNTAX      Integer32(1..28)
   MAX-ACCESS  not-accessible
   STATUS      current
   DESCRIPTION
       " "
   ::= { opmen99810bIPSourceGuardStaticEntry 1 }

opmen99810bIPSourceGuardStaticPort OBJECT-TYPE
   SYNTAX      Integer32(1..4095)
   MAX-ACCESS  read-write
   STATUS      current
   DESCRIPTION
       " Port, range: 1 - port number. "
   ::= { opmen99810bIPSourceGuardStaticEntry 2 }

opmen99810bIPSourceGuardStaticVLANId OBJECT-TYPE
   SYNTAX      Integer32(1..4094)
   MAX-ACCESS  read-write
   STATUS      current
   DESCRIPTION
       " VLAN ID, range: 1 - 4094. "
   ::= { opmen99810bIPSourceGuardStaticEntry 3 }

opmen99810bIPSourceGuardStaticIPAddress OBJECT-TYPE
   SYNTAX      IpAddress
   MAX-ACCESS  read-write
   STATUS      current
   DESCRIPTION
       " IP address allowed for doing IP source guard. "
   ::= { opmen99810bIPSourceGuardStaticEntry 4 }

opmen99810bIPSourceGuardStaticMACAddress OBJECT-TYPE
   SYNTAX      MacAddress
   MAX-ACCESS  read-write
   STATUS      current
   DESCRIPTION
       " Allowed Source MAC address, format 0a 1b 2c 3d 4e 5f "
   ::= { opmen99810bIPSourceGuardStaticEntry 5 }

opmen99810bIPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { opmen99810bIPSourceGuardStaticEntry 6 }

opmen99810bIPSourceGuardDynamicTable OBJECT-TYPE
   SYNTAX      SEQUENCE OF Opmen99810bIPSourceGuardDynamicEntry
   MAX-ACCESS  not-accessible
   STATUS      current
   DESCRIPTION
       " "
   ::= { opmen99810bIPSourceGuard 3 }

opmen99810bIPSourceGuardDynamicEntry OBJECT-TYPE
   SYNTAX      Opmen99810bIPSourceGuardDynamicEntry
   MAX-ACCESS  not-accessible
   STATUS      current
   DESCRIPTION
       ""
   INDEX    { opmen99810bIPSourceGuardDynamicIndex  }
   ::= { opmen99810bIPSourceGuardDynamicTable 1 }

Opmen99810bIPSourceGuardDynamicEntry ::= SEQUENCE {
   opmen99810bIPSourceGuardDynamicIndex          Integer32,
   opmen99810bIPSourceGuardDynamicPort           Integer32,
   opmen99810bIPSourceGuardDynamicVLANId         Integer32,
   opmen99810bIPSourceGuardDynamicIPAddress      IpAddress,
   opmen99810bIPSourceGuardDynamicMACAddress     MacAddress
}

opmen99810bIPSourceGuardDynamicIndex OBJECT-TYPE
   SYNTAX      Integer32(1..4095)
   MAX-ACCESS  not-accessible
   STATUS      current
   DESCRIPTION
       " "
   ::= { opmen99810bIPSourceGuardDynamicEntry 1 }

opmen99810bIPSourceGuardDynamicPort OBJECT-TYPE
   SYNTAX      Integer32(1..10)
   MAX-ACCESS  read-only
   STATUS      current
   DESCRIPTION
       " "
   ::= { opmen99810bIPSourceGuardDynamicEntry 2 }

opmen99810bIPSourceGuardDynamicVLANId OBJECT-TYPE
   SYNTAX      Integer32(1..4094)
   MAX-ACCESS  read-only
   STATUS      current
   DESCRIPTION
       " "
   ::= { opmen99810bIPSourceGuardDynamicEntry 3 }

opmen99810bIPSourceGuardDynamicIPAddress OBJECT-TYPE
   SYNTAX      IpAddress
   MAX-ACCESS  read-only
   STATUS      current
   DESCRIPTION
       " "
   ::= { opmen99810bIPSourceGuardDynamicEntry 4 }

opmen99810bIPSourceGuardDynamicMACAddress OBJECT-TYPE
   SYNTAX      MacAddress
   MAX-ACCESS  read-only
   STATUS      current
   DESCRIPTION
       " "
   ::= { opmen99810bIPSourceGuardDynamicEntry 5 }

opmen99810bARPInspection                                         OBJECT IDENTIFIER ::= { opmen99810bSecurity 2 }

opmen99810bARPInspectionConf                                     OBJECT IDENTIFIER ::= { opmen99810bARPInspection 1 }

opmen99810bARPInspectionConfMode OBJECT-TYPE
   SYNTAX      INTEGER { disable(0), enable(1) }
   MAX-ACCESS  read-write
   STATUS      current
   DESCRIPTION
       "default: 0
        0: disable
        1: enable"
   ::= { opmen99810bARPInspectionConf 1 }

opmen99810bARPInspectionConfTable OBJECT-TYPE
   SYNTAX      SEQUENCE OF Opmen99810bARPInspectionConfEntry
   MAX-ACCESS  not-accessible
   STATUS      current
   DESCRIPTION
       " "
   ::= { opmen99810bARPInspectionConf 2 }

opmen99810bARPInspectionConfEntry OBJECT-TYPE
   SYNTAX      Opmen99810bARPInspectionConfEntry
   MAX-ACCESS  not-accessible
   STATUS      current
   DESCRIPTION
       ""
   INDEX    { opmen99810bARPInspectionConfPortIndex  }
   ::= { opmen99810bARPInspectionConfTable 1 }

Opmen99810bARPInspectionConfEntry ::= SEQUENCE {
   opmen99810bARPInspectionConfPortIndex	Integer32,
   opmen99810bARPInspectionConfPortMode	INTEGER
}

opmen99810bARPInspectionConfPortIndex OBJECT-TYPE
   SYNTAX      Integer32(1..4095)
   MAX-ACCESS  not-accessible
   STATUS      current
   DESCRIPTION
       " "
   ::= { opmen99810bARPInspectionConfEntry 1 }

opmen99810bARPInspectionConfPortMode OBJECT-TYPE
   SYNTAX      INTEGER { disable(0), enable(1) }
   MAX-ACCESS  read-write
   STATUS      current
   DESCRIPTION
       "default: 0
        0: disable
        1: enable"
   ::= { opmen99810bARPInspectionConfEntry 2 }


opmen99810bARPInspectionStatic                                OBJECT IDENTIFIER ::= { opmen99810bARPInspection 2 }

opmen99810bARPInspectionStaticCreate OBJECT-TYPE
   SYNTAX      INTEGER { none(0), create(1) }
   MAX-ACCESS  read-write
   STATUS      current
   DESCRIPTION
       "default: 0
        0: none
        1: create"
   ::= { opmen99810bARPInspectionStatic 1 }

opmen99810bARPInspectionStaticTable OBJECT-TYPE
   SYNTAX      SEQUENCE OF Opmen99810bARPInspectionStaticEntry
   MAX-ACCESS  not-accessible
   STATUS      current
   DESCRIPTION
       " "
   ::= { opmen99810bARPInspectionStatic 2 }

opmen99810bARPInspectionStaticEntry OBJECT-TYPE
   SYNTAX      Opmen99810bARPInspectionStaticEntry
   MAX-ACCESS  not-accessible
   STATUS      current
   DESCRIPTION
       ""
   INDEX    { opmen99810bARPInspectionStaticIndex  }
   ::= { opmen99810bARPInspectionStaticTable 1 }

Opmen99810bARPInspectionStaticEntry ::= SEQUENCE {
   opmen99810bARPInspectionStaticIndex       Integer32,
   opmen99810bARPInspectionStaticPort        Integer32,
   opmen99810bARPInspectionStaticVLANId      Integer32,
   opmen99810bARPInspectionStaticIPAddress   IpAddress,
   opmen99810bARPInspectionStaticMACAddress  MacAddress,
   opmen99810bARPInspectionStaticRowStatus   INTEGER
}

opmen99810bARPInspectionStaticIndex OBJECT-TYPE
   SYNTAX      Integer32(1..4095)
   MAX-ACCESS  not-accessible
   STATUS      current
   DESCRIPTION
       ""
   ::= { opmen99810bARPInspectionStaticEntry 1 }

opmen99810bARPInspectionStaticPort OBJECT-TYPE
   SYNTAX      Integer32(1..4095)
   MAX-ACCESS  read-write
   STATUS      current
   DESCRIPTION
       " Port, range: 1 - port number. "
   ::= { opmen99810bARPInspectionStaticEntry 2 }

opmen99810bARPInspectionStaticVLANId OBJECT-TYPE
   SYNTAX      Integer32(1..4094)
   MAX-ACCESS  read-write
   STATUS      current
   DESCRIPTION
       " VLAN ID, range: 1 - 4094. "
   ::= { opmen99810bARPInspectionStaticEntry 3 }

opmen99810bARPInspectionStaticIPAddress OBJECT-TYPE
   SYNTAX      IpAddress
   MAX-ACCESS  read-write
   STATUS      current
   DESCRIPTION
       " IP address allowed for doing ARP request. "
   ::= { opmen99810bARPInspectionStaticEntry 4 }

opmen99810bARPInspectionStaticMACAddress OBJECT-TYPE
   SYNTAX      MacAddress
   MAX-ACCESS  read-write
   STATUS      current
   DESCRIPTION
       " Allowed Source MAC address in ARP request packets, format 0a 1b 2c 3d 4e 5f "
   ::= { opmen99810bARPInspectionStaticEntry 5 }

opmen99810bARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { opmen99810bARPInspectionStaticEntry 6 }

opmen99810bARPInspectionDynamicTable OBJECT-TYPE
   SYNTAX      SEQUENCE OF Opmen99810bARPInspectionDynamicEntry
   MAX-ACCESS  not-accessible
   STATUS      current
   DESCRIPTION
       " "
   ::= { opmen99810bARPInspection 3 }

opmen99810bARPInspectionDynamicEntry OBJECT-TYPE
   SYNTAX      Opmen99810bARPInspectionDynamicEntry
   MAX-ACCESS  not-accessible
   STATUS      current
   DESCRIPTION
       ""
   INDEX    { opmen99810bARPInspectionDynamicIndex  }
   ::= { opmen99810bARPInspectionDynamicTable 1 }

Opmen99810bARPInspectionDynamicEntry ::= SEQUENCE {
   opmen99810bARPInspectionDynamicIndex          Integer32,
   opmen99810bARPInspectionDynamicPort           Integer32,
   opmen99810bARPInspectionDynamicVLANId         Integer32,
   opmen99810bARPInspectionDynamicIPAddress      IpAddress,
   opmen99810bARPInspectionDynamicMACAddress     MacAddress
}

opmen99810bARPInspectionDynamicIndex OBJECT-TYPE
   SYNTAX      Integer32(1..4095)
   MAX-ACCESS  not-accessible
   STATUS      current
   DESCRIPTION
       " "
   ::= { opmen99810bARPInspectionDynamicEntry 1 }

opmen99810bARPInspectionDynamicPort OBJECT-TYPE
   SYNTAX      Integer32(1..4095)
   MAX-ACCESS  read-only
   STATUS      current
   DESCRIPTION
       ""
   ::= { opmen99810bARPInspectionDynamicEntry 2 }

opmen99810bARPInspectionDynamicVLANId OBJECT-TYPE
   SYNTAX      Integer32(1..4094)
   MAX-ACCESS  read-only
   STATUS      current
   DESCRIPTION
       ""
   ::= { opmen99810bARPInspectionDynamicEntry 3 }

opmen99810bARPInspectionDynamicIPAddress OBJECT-TYPE
   SYNTAX      IpAddress
   MAX-ACCESS  read-only
   STATUS      current
   DESCRIPTION
       ""
   ::= { opmen99810bARPInspectionDynamicEntry 4 }

opmen99810bARPInspectionDynamicMACAddress OBJECT-TYPE
   SYNTAX      MacAddress
   MAX-ACCESS  read-only
   STATUS      current
   DESCRIPTION
       ""
   ::= { opmen99810bARPInspectionDynamicEntry 5 }

opmen99810bDHCPSnooping                                          OBJECT IDENTIFIER ::= { opmen99810bSecurity 3 }

opmen99810bDHCPSnoopingConf                                          OBJECT IDENTIFIER ::= { opmen99810bDHCPSnooping 1 }

opmen99810bDHCPSnoopingMode OBJECT-TYPE
   SYNTAX      INTEGER { disable(0), enable(1) }
   MAX-ACCESS  read-write
   STATUS      current
   DESCRIPTION
       "default: 0
       0: disable
       1: enable"
   ::= { opmen99810bDHCPSnoopingConf 1 }

opmen99810bDHCPSnoopingPortModeConfigurationTable OBJECT-TYPE
   SYNTAX      SEQUENCE OF Opmen99810bDHCPSnoopingPortModeConfigurationEntry
   MAX-ACCESS  not-accessible
   STATUS      current
   DESCRIPTION
       " "
   ::= { opmen99810bDHCPSnoopingConf 2 }

opmen99810bDHCPSnoopingPortModeConfigurationEntry OBJECT-TYPE
   SYNTAX      Opmen99810bDHCPSnoopingPortModeConfigurationEntry
   MAX-ACCESS  not-accessible
   STATUS      current
   DESCRIPTION
       ""
   INDEX    { opmen99810bDHCPSnoopingPortModeConfigurationPort  }
   ::= { opmen99810bDHCPSnoopingPortModeConfigurationTable 1 }

Opmen99810bDHCPSnoopingPortModeConfigurationEntry ::= SEQUENCE {
   opmen99810bDHCPSnoopingPortModeConfigurationPort	Integer32,
   opmen99810bDHCPSnoopingPortModeConfigurationMode	INTEGER
}

opmen99810bDHCPSnoopingPortModeConfigurationPort OBJECT-TYPE
   SYNTAX      Integer32(1..4095)
   MAX-ACCESS  not-accessible
   STATUS      current
   DESCRIPTION
       " "
   ::= { opmen99810bDHCPSnoopingPortModeConfigurationEntry 1 }

opmen99810bDHCPSnoopingPortModeConfigurationMode OBJECT-TYPE
   SYNTAX      INTEGER { trust(0), untrust(1) }
   MAX-ACCESS  read-write
   STATUS      current
   DESCRIPTION
       "default: 1
       0: trust port mode
       1: untrust port mode"
   ::= { opmen99810bDHCPSnoopingPortModeConfigurationEntry 2 }

opmen99810bDHCPSnoopingStatisticsTable OBJECT-TYPE
   SYNTAX      SEQUENCE OF Opmen99810bDHCPSnoopingStatisticsEntry
   MAX-ACCESS  not-accessible
   STATUS      current
   DESCRIPTION
       " "
   ::= { opmen99810bDHCPSnooping 2 }

opmen99810bDHCPSnoopingStatisticsEntry OBJECT-TYPE
   SYNTAX      Opmen99810bDHCPSnoopingStatisticsEntry
   MAX-ACCESS  not-accessible
   STATUS      current
   DESCRIPTION
       ""
   INDEX    { opmen99810bDHCPSnoopingStatisticsPort  }
   ::= { opmen99810bDHCPSnoopingStatisticsTable 1 }

Opmen99810bDHCPSnoopingStatisticsEntry ::= SEQUENCE {
   opmen99810bDHCPSnoopingStatisticsPort         Integer32,
   opmen99810bDHCPSnoopingStatisticsClear        INTEGER,
   opmen99810bDHCPSnoopingRxDiscover             Counter32,
   opmen99810bDHCPSnoopingRxOffer                Counter32,
   opmen99810bDHCPSnoopingRxRequest              Counter32,
   opmen99810bDHCPSnoopingRxDecline              Counter32,
   opmen99810bDHCPSnoopingRxACK                  Counter32,
   opmen99810bDHCPSnoopingRxNAK                  Counter32,
   opmen99810bDHCPSnoopingRxRelease              Counter32,
   opmen99810bDHCPSnoopingRxInform               Counter32,
   opmen99810bDHCPSnoopingRxLeaseQuery           Counter32,
   opmen99810bDHCPSnoopingRxLeaseUnassigned      Counter32,
   opmen99810bDHCPSnoopingRxLeaseUnknown         Counter32,
   opmen99810bDHCPSnoopingRxLeaseActive          Counter32,
   opmen99810bDHCPSnoopingTxDiscover             Counter32,
   opmen99810bDHCPSnoopingTxOffer                Counter32,
   opmen99810bDHCPSnoopingTxRequest              Counter32,
   opmen99810bDHCPSnoopingTxDecline              Counter32,
   opmen99810bDHCPSnoopingTxACK                  Counter32,
   opmen99810bDHCPSnoopingTxNAK                  Counter32,
   opmen99810bDHCPSnoopingTxRelease              Counter32,
   opmen99810bDHCPSnoopingTxInform               Counter32,
   opmen99810bDHCPSnoopingTxLeaseQuery           Counter32,
   opmen99810bDHCPSnoopingTxLeaseUnassigned      Counter32,
   opmen99810bDHCPSnoopingTxLeaseUnknown         Counter32,
   opmen99810bDHCPSnoopingTxLeaseActive          Counter32
}

opmen99810bDHCPSnoopingStatisticsPort OBJECT-TYPE
   SYNTAX      Integer32(1..4095)
   MAX-ACCESS  not-accessible
   STATUS      current
   DESCRIPTION
       " "
   ::= { opmen99810bDHCPSnoopingStatisticsEntry 1 }

opmen99810bDHCPSnoopingStatisticsClear OBJECT-TYPE
   SYNTAX      INTEGER { none(0), clear(1) }
   MAX-ACCESS  read-write
   STATUS      current
   DESCRIPTION
       "default: 0
       0: none
       1: clear"
   ::= { opmen99810bDHCPSnoopingStatisticsEntry 2 }

opmen99810bDHCPSnoopingRxDiscover OBJECT-TYPE
   SYNTAX      Counter32
   MAX-ACCESS  read-only
   STATUS      current
   DESCRIPTION
       " "
   ::= { opmen99810bDHCPSnoopingStatisticsEntry 3 }

opmen99810bDHCPSnoopingRxOffer OBJECT-TYPE
   SYNTAX      Counter32
   MAX-ACCESS  read-only
   STATUS      current
   DESCRIPTION
       " "
   ::= { opmen99810bDHCPSnoopingStatisticsEntry 4 }

opmen99810bDHCPSnoopingRxRequest OBJECT-TYPE
   SYNTAX      Counter32
   MAX-ACCESS  read-only
   STATUS      current
   DESCRIPTION
       " "
   ::= { opmen99810bDHCPSnoopingStatisticsEntry 5 }

opmen99810bDHCPSnoopingRxDecline OBJECT-TYPE
   SYNTAX      Counter32
   MAX-ACCESS  read-only
   STATUS      current
   DESCRIPTION
       " "
   ::= { opmen99810bDHCPSnoopingStatisticsEntry 6 }

opmen99810bDHCPSnoopingRxACK OBJECT-TYPE
   SYNTAX      Counter32
   MAX-ACCESS  read-only
   STATUS      current
   DESCRIPTION
       " "
   ::= { opmen99810bDHCPSnoopingStatisticsEntry 7 }

opmen99810bDHCPSnoopingRxNAK OBJECT-TYPE
   SYNTAX      Counter32
   MAX-ACCESS  read-only
   STATUS      current
   DESCRIPTION
       " "
   ::= { opmen99810bDHCPSnoopingStatisticsEntry 8 }

opmen99810bDHCPSnoopingRxRelease OBJECT-TYPE
   SYNTAX      Counter32
   MAX-ACCESS  read-only
   STATUS      current
   DESCRIPTION
       " "
   ::= { opmen99810bDHCPSnoopingStatisticsEntry 9 }

opmen99810bDHCPSnoopingRxInform OBJECT-TYPE
   SYNTAX      Counter32
   MAX-ACCESS  read-only
   STATUS      current
   DESCRIPTION
       " "
   ::= { opmen99810bDHCPSnoopingStatisticsEntry 10 }

opmen99810bDHCPSnoopingRxLeaseQuery OBJECT-TYPE
   SYNTAX      Counter32
   MAX-ACCESS  read-only
   STATUS      current
   DESCRIPTION
       " "
   ::= { opmen99810bDHCPSnoopingStatisticsEntry 11 }

opmen99810bDHCPSnoopingRxLeaseUnassigned OBJECT-TYPE
   SYNTAX      Counter32
   MAX-ACCESS  read-only
   STATUS      current
   DESCRIPTION
       " "
   ::= { opmen99810bDHCPSnoopingStatisticsEntry 12 }

opmen99810bDHCPSnoopingRxLeaseUnknown OBJECT-TYPE
   SYNTAX      Counter32
   MAX-ACCESS  read-only
   STATUS      current
   DESCRIPTION
       " "
   ::= { opmen99810bDHCPSnoopingStatisticsEntry 13 }

opmen99810bDHCPSnoopingRxLeaseActive OBJECT-TYPE
   SYNTAX      Counter32
   MAX-ACCESS  read-only
   STATUS      current
   DESCRIPTION
       " "
   ::= { opmen99810bDHCPSnoopingStatisticsEntry 14 }

opmen99810bDHCPSnoopingTxDiscover OBJECT-TYPE
   SYNTAX      Counter32
   MAX-ACCESS  read-only
   STATUS      current
   DESCRIPTION
       " "
   ::= { opmen99810bDHCPSnoopingStatisticsEntry 15 }

opmen99810bDHCPSnoopingTxOffer OBJECT-TYPE
   SYNTAX      Counter32
   MAX-ACCESS  read-only
   STATUS      current
   DESCRIPTION
       " "
   ::= { opmen99810bDHCPSnoopingStatisticsEntry 16 }

opmen99810bDHCPSnoopingTxRequest OBJECT-TYPE
   SYNTAX      Counter32
   MAX-ACCESS  read-only
   STATUS      current
   DESCRIPTION
       " "
   ::= { opmen99810bDHCPSnoopingStatisticsEntry 17 }

opmen99810bDHCPSnoopingTxDecline OBJECT-TYPE
   SYNTAX      Counter32
   MAX-ACCESS  read-only
   STATUS      current
   DESCRIPTION
       " "
   ::= { opmen99810bDHCPSnoopingStatisticsEntry 18 }

opmen99810bDHCPSnoopingTxACK OBJECT-TYPE
   SYNTAX      Counter32
   MAX-ACCESS  read-only
   STATUS      current
   DESCRIPTION
       " "
   ::= { opmen99810bDHCPSnoopingStatisticsEntry 19 }

opmen99810bDHCPSnoopingTxNAK OBJECT-TYPE
   SYNTAX      Counter32
   MAX-ACCESS  read-only
   STATUS      current
   DESCRIPTION
       " "
   ::= { opmen99810bDHCPSnoopingStatisticsEntry 20 }

opmen99810bDHCPSnoopingTxRelease OBJECT-TYPE
   SYNTAX      Counter32
   MAX-ACCESS  read-only
   STATUS      current
   DESCRIPTION
       " "
   ::= { opmen99810bDHCPSnoopingStatisticsEntry 21 }

opmen99810bDHCPSnoopingTxInform OBJECT-TYPE
   SYNTAX      Counter32
   MAX-ACCESS  read-only
   STATUS      current
   DESCRIPTION
       " "
   ::= { opmen99810bDHCPSnoopingStatisticsEntry 22 }

opmen99810bDHCPSnoopingTxLeaseQuery OBJECT-TYPE
   SYNTAX      Counter32
   MAX-ACCESS  read-only
   STATUS      current
   DESCRIPTION
       " "
   ::= { opmen99810bDHCPSnoopingStatisticsEntry 23 }

opmen99810bDHCPSnoopingTxLeaseUnassigned OBJECT-TYPE
   SYNTAX      Counter32
   MAX-ACCESS  read-only
   STATUS      current
   DESCRIPTION
       " "
   ::= { opmen99810bDHCPSnoopingStatisticsEntry 24 }

opmen99810bDHCPSnoopingTxLeaseUnknown OBJECT-TYPE
   SYNTAX      Counter32
   MAX-ACCESS  read-only
   STATUS      current
   DESCRIPTION
       " "
   ::= { opmen99810bDHCPSnoopingStatisticsEntry 25 }

opmen99810bDHCPSnoopingTxLeaseActive OBJECT-TYPE
   SYNTAX      Counter32
   MAX-ACCESS  read-only
   STATUS      current
   DESCRIPTION
       " "
   ::= { opmen99810bDHCPSnoopingStatisticsEntry 26 }


opmen99810bDHCPRelay                                             OBJECT IDENTIFIER ::= { opmen99810bSecurity 4 }

opmen99810bDHCPRelayConfiguration                                         OBJECT IDENTIFIER ::= { opmen99810bDHCPRelay 1 }

opmen99810bDHCPRelayMode OBJECT-TYPE
   SYNTAX      INTEGER { disable(0), enable(1) }
   MAX-ACCESS  read-write
   STATUS      current
   DESCRIPTION
       "default: 0
       0: disable
       1: enable
       We need at least one server"
   ::= { opmen99810bDHCPRelayConfiguration 1 }

opmen99810bDHCPRelayServer OBJECT-TYPE
   SYNTAX      IpAddress
   MAX-ACCESS  read-write
   STATUS      current
   DESCRIPTION
       " "
   ::= { opmen99810bDHCPRelayConfiguration 2 }

opmen99810bDHCPRelayInformationMode OBJECT-TYPE
   SYNTAX      INTEGER { disable(0), enable(1) }
   MAX-ACCESS  read-write
   STATUS      current
   DESCRIPTION
       "default: 0
       0: disable
       1: enable "
   ::= { opmen99810bDHCPRelayConfiguration 3 }

opmen99810bDHCPRelayInformationPolicy OBJECT-TYPE
   SYNTAX      INTEGER { replace(0), keep(1), drop(2) }
   MAX-ACCESS  read-write
   STATUS      current
   DESCRIPTION
       "default: 0
       0: replace
       1: keep
       2: drop "
   ::= { opmen99810bDHCPRelayConfiguration 4 }

opmen99810bDHCPRelayStatistics                                   OBJECT IDENTIFIER ::= { opmen99810bDHCPRelay 2 }

opmen99810bDHCPRelayServerStatistics                                   OBJECT IDENTIFIER ::= { opmen99810bDHCPRelayStatistics 1 }

opmen99810bServerStatTransmitToServer OBJECT-TYPE
   SYNTAX      Counter32
   MAX-ACCESS  read-only
   STATUS      current
   DESCRIPTION
       " "
   ::= { opmen99810bDHCPRelayServerStatistics 1 }

opmen99810bServerStatTransmitError OBJECT-TYPE
   SYNTAX      Counter32
   MAX-ACCESS  read-only
   STATUS      current
   DESCRIPTION
       " "
   ::= { opmen99810bDHCPRelayServerStatistics 2 }

opmen99810bServerStatReceiveFromServer OBJECT-TYPE
   SYNTAX      Counter32
   MAX-ACCESS  read-only
   STATUS      current
   DESCRIPTION
       " "
   ::= { opmen99810bDHCPRelayServerStatistics 3 }

opmen99810bServerStatReceiveMissingAgentOption OBJECT-TYPE
   SYNTAX      Counter32
   MAX-ACCESS  read-only
   STATUS      current
   DESCRIPTION
       " "
   ::= { opmen99810bDHCPRelayServerStatistics 4 }

opmen99810bServerStatReceiveMissingCircuitID OBJECT-TYPE
   SYNTAX      Counter32
   MAX-ACCESS  read-only
   STATUS      current
   DESCRIPTION
       " "
   ::= { opmen99810bDHCPRelayServerStatistics 5 }

opmen99810bServerStatReceiveMissingRemoteID OBJECT-TYPE
   SYNTAX      Counter32
   MAX-ACCESS  read-only
   STATUS      current
   DESCRIPTION
       " "
   ::= { opmen99810bDHCPRelayServerStatistics 6 }

opmen99810bServerStatReceiveBadCircuitID OBJECT-TYPE
   SYNTAX      Counter32
   MAX-ACCESS  read-only
   STATUS      current
   DESCRIPTION
       " "
   ::= { opmen99810bDHCPRelayServerStatistics 7 }

opmen99810bServerStatReceiveBadRemoteID OBJECT-TYPE
   SYNTAX      Counter32
   MAX-ACCESS  read-only
   STATUS      current
   DESCRIPTION
       " "
   ::= { opmen99810bDHCPRelayServerStatistics 8 }

opmen99810bDHCPRelayClientStatistics                                   OBJECT IDENTIFIER ::= { opmen99810bDHCPRelayStatistics 2 }

opmen99810bClientStatTransmitToClient OBJECT-TYPE
   SYNTAX      Counter32
   MAX-ACCESS  read-only
   STATUS      current
   DESCRIPTION
       " "
   ::= { opmen99810bDHCPRelayClientStatistics 1 }

opmen99810bClientStatTransmitError OBJECT-TYPE
   SYNTAX      Counter32
   MAX-ACCESS  read-only
   STATUS      current
   DESCRIPTION
       " "
   ::= { opmen99810bDHCPRelayClientStatistics 2 }

opmen99810bClientStatReceivefromClient OBJECT-TYPE
   SYNTAX      Counter32
   MAX-ACCESS  read-only
   STATUS      current
   DESCRIPTION
       " "
   ::= { opmen99810bDHCPRelayClientStatistics 3 }

opmen99810bClientStatReceiveAgentOption OBJECT-TYPE
   SYNTAX      Counter32
   MAX-ACCESS  read-only
   STATUS      current
   DESCRIPTION
       " "
   ::= { opmen99810bDHCPRelayClientStatistics 4 }

opmen99810bClientStatReplaceAgentOption OBJECT-TYPE
   SYNTAX      Counter32
   MAX-ACCESS  read-only
   STATUS      current
   DESCRIPTION
       " "
   ::= { opmen99810bDHCPRelayClientStatistics 5 }

opmen99810bClientStatKeepAgentOption OBJECT-TYPE
   SYNTAX      Counter32
   MAX-ACCESS  read-only
   STATUS      current
   DESCRIPTION
       " "
   ::= { opmen99810bDHCPRelayClientStatistics 6 }

opmen99810bClientStatDropAgentOption OBJECT-TYPE
   SYNTAX      Counter32
   MAX-ACCESS  read-only
   STATUS      current
   DESCRIPTION
       " "
   ::= { opmen99810bDHCPRelayClientStatistics 7 }

opmen99810bPortSecurity                                          OBJECT IDENTIFIER ::= { opmen99810bSecurity 5 }

opmen99810bPortSecLimitCtrl                                      OBJECT IDENTIFIER ::= { opmen99810bPortSecurity 1 }

opmen99810bPortSecLimitCtrlSystemConf                                      OBJECT IDENTIFIER ::= { opmen99810bPortSecLimitCtrl 1 }

opmen99810bPortSecurityMode OBJECT-TYPE
   SYNTAX      INTEGER { disable(0), enable(1) }
   MAX-ACCESS  read-write
   STATUS      current
   DESCRIPTION
       "default: 0
       0: disable
       1: enable "
   ::= { opmen99810bPortSecLimitCtrlSystemConf 1 }

opmen99810bPortSecurityAging OBJECT-TYPE
   SYNTAX      INTEGER { disable(0), enable(1) }
   MAX-ACCESS  read-write
   STATUS      current
   DESCRIPTION
       "default: 0
       0: disable
       1: enable "
   ::= { opmen99810bPortSecLimitCtrlSystemConf 2 }

opmen99810bPortSecurityAgingPeriod OBJECT-TYPE
   SYNTAX      INTEGER(10..10000000)
   MAX-ACCESS  read-write
   STATUS      current
   DESCRIPTION
       "default: 3600, range: 10-10000000 "
   ::= { opmen99810bPortSecLimitCtrlSystemConf 3 }

opmen99810bPortSecLimitCtrlTable OBJECT-TYPE
   SYNTAX      SEQUENCE OF Opmen99810bPortSecLimitCtrlEntry
   MAX-ACCESS  not-accessible
   STATUS      current
   DESCRIPTION
       " "
   ::= { opmen99810bPortSecLimitCtrl 2 }

opmen99810bPortSecLimitCtrlEntry OBJECT-TYPE
   SYNTAX      Opmen99810bPortSecLimitCtrlEntry
   MAX-ACCESS  not-accessible
   STATUS      current
   DESCRIPTION
       ""
   INDEX    { opmen99810bPortSecLimitCtrlPort  }
   ::= { opmen99810bPortSecLimitCtrlTable 1 }

Opmen99810bPortSecLimitCtrlEntry ::= SEQUENCE {
   opmen99810bPortSecLimitCtrlPort           Integer32,
   opmen99810bPortSecLimitCtrlPortMode       INTEGER,
   opmen99810bPortSecLimitCtrlPortLimit      Integer32,
   opmen99810bPortSecLimitCtrlPortAction     INTEGER,
   opmen99810bPortSecLimitCtrlPortState      DisplayString,
   opmen99810bPortSecLimitCtrlPortReOpen     INTEGER
}

opmen99810bPortSecLimitCtrlPort OBJECT-TYPE
   SYNTAX      Integer32(1..4095)
   MAX-ACCESS  not-accessible
   STATUS      current
   DESCRIPTION
       " "
   ::= { opmen99810bPortSecLimitCtrlEntry 1 }

opmen99810bPortSecLimitCtrlPortMode OBJECT-TYPE
   SYNTAX      INTEGER { disable(0), enable(1) }
   MAX-ACCESS  read-write
   STATUS      current
   DESCRIPTION
       "default: 0
       0: disable
       1: enable"
   ::= { opmen99810bPortSecLimitCtrlEntry 2 }

opmen99810bPortSecLimitCtrlPortLimit OBJECT-TYPE
   SYNTAX      Integer32(1..1024)
   MAX-ACCESS  read-write
   STATUS      current
   DESCRIPTION
       "default: 4, range: 1-1024"
   ::= { opmen99810bPortSecLimitCtrlEntry 3 }

opmen99810bPortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { opmen99810bPortSecLimitCtrlEntry 4 }

opmen99810bPortSecLimitCtrlPortState OBJECT-TYPE
   SYNTAX      DisplayString
   MAX-ACCESS  read-only
   STATUS      current
   DESCRIPTION
       ""
   ::= { opmen99810bPortSecLimitCtrlEntry 5 }

opmen99810bPortSecLimitCtrlPortReOpen OBJECT-TYPE
   SYNTAX      INTEGER { none(0), reopen(1) }
   MAX-ACCESS  read-write
   STATUS      current
   DESCRIPTION
       "default: 0
       0: none
       1: reopen"
   ::= { opmen99810bPortSecLimitCtrlEntry 6 }

opmen99810bPortSecSwitchStatusTable OBJECT-TYPE
   SYNTAX      SEQUENCE OF Opmen99810bPortSecSwitchStatusEntry
   MAX-ACCESS  not-accessible
   STATUS      current
   DESCRIPTION
       " "
   ::= { opmen99810bPortSecurity 2 }

opmen99810bPortSecSwitchStatusEntry OBJECT-TYPE
   SYNTAX      Opmen99810bPortSecSwitchStatusEntry
   MAX-ACCESS  not-accessible
   STATUS      current
   DESCRIPTION
       ""
   INDEX    { opmen99810bPortSecSwitchStatusPort  }
   ::= { opmen99810bPortSecSwitchStatusTable 1 }

Opmen99810bPortSecSwitchStatusEntry ::= SEQUENCE {
   opmen99810bPortSecSwitchStatusPort                Integer32,
   opmen99810bPortSecSwitchStatusUsers               DisplayString,
   opmen99810bPortSecSwitchStatusState               DisplayString,
   opmen99810bPortSecSwitchStatusMACCountCurrent     Integer32,
   opmen99810bPortSecSwitchStatusMACCountLimit       Integer32
}

opmen99810bPortSecSwitchStatusPort OBJECT-TYPE
   SYNTAX      Integer32(1..4095)
   MAX-ACCESS  not-accessible
   STATUS      current
   DESCRIPTION
       " "
   ::= { opmen99810bPortSecSwitchStatusEntry 1 }

opmen99810bPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { opmen99810bPortSecSwitchStatusEntry 2 }

opmen99810bPortSecSwitchStatusState OBJECT-TYPE
   SYNTAX      DisplayString
   MAX-ACCESS  read-only
   STATUS      current
   DESCRIPTION
       " Shows the current state of the port : Disabled, Ready, Limit Reached, Shutdown. "
   ::= { opmen99810bPortSecSwitchStatusEntry 3 }

opmen99810bPortSecSwitchStatusMACCountCurrent OBJECT-TYPE
   SYNTAX      Integer32(1..4095)
   MAX-ACCESS  read-only
   STATUS      current
   DESCRIPTION
       ""
   ::= { opmen99810bPortSecSwitchStatusEntry 4 }

opmen99810bPortSecSwitchStatusMACCountLimit OBJECT-TYPE
   SYNTAX      Integer32(1..4095)
   MAX-ACCESS  read-only
   STATUS      current
   DESCRIPTION
       ""
   ::= { opmen99810bPortSecSwitchStatusEntry 5 }

opmen99810bPortSecPortStatus                                      OBJECT IDENTIFIER ::= { opmen99810bPortSecurity 3 }

opmen99810bPortSecPortStatusPort OBJECT-TYPE
   SYNTAX       Integer32(1..4095)
   MAX-ACCESS   read-write
   STATUS       current
   DESCRIPTION
       "port number
        default: 1
        range: 1 - port number."
   ::= { opmen99810bPortSecPortStatus 1 }

opmen99810bPortSecPortStatusTable OBJECT-TYPE
   SYNTAX      SEQUENCE OF Opmen99810bPortSecPortStatusEntry
   MAX-ACCESS  not-accessible
   STATUS      current
   DESCRIPTION
      " "
   ::= { opmen99810bPortSecPortStatus 2 }

opmen99810bPortSecPortStatusEntry OBJECT-TYPE
   SYNTAX      Opmen99810bPortSecPortStatusEntry
   MAX-ACCESS  not-accessible
   STATUS      current
   DESCRIPTION
       ""
   INDEX    { opmen99810bPortSecPortStatusIndex  }
   ::= { opmen99810bPortSecPortStatusTable 1 }

Opmen99810bPortSecPortStatusEntry ::= SEQUENCE {
   opmen99810bPortSecPortStatusIndex              Integer32,
   opmen99810bPortSecPortStatusMACAddress         MacAddress,
   opmen99810bPortSecPortStatusVLANId             Integer32,
   opmen99810bPortSecPortStatusState              DisplayString,
   opmen99810bPortSecPortStatusTimeOfAddition     DisplayString,
   opmen99810bPortSecPortStatusAgeAndHold         DisplayString
}

opmen99810bPortSecPortStatusIndex OBJECT-TYPE
   SYNTAX      Integer32(1..4095)
   MAX-ACCESS  not-accessible
   STATUS      current
   DESCRIPTION
       " "
   ::= { opmen99810bPortSecPortStatusEntry 1 }

opmen99810bPortSecPortStatusMACAddress OBJECT-TYPE
   SYNTAX      MacAddress
   MAX-ACCESS  read-only
   STATUS      current
   DESCRIPTION
       " "
   ::= { opmen99810bPortSecPortStatusEntry 2 }

opmen99810bPortSecPortStatusVLANId OBJECT-TYPE
   SYNTAX      Integer32(1..4094)
   MAX-ACCESS  read-only
   STATUS      current
   DESCRIPTION
       " "
   ::= { opmen99810bPortSecPortStatusEntry 3 }

opmen99810bPortSecPortStatusState OBJECT-TYPE
   SYNTAX      DisplayString
   MAX-ACCESS  read-only
   STATUS      current
   DESCRIPTION
       "Blocked / Forwarding "
   ::= { opmen99810bPortSecPortStatusEntry 4 }

opmen99810bPortSecPortStatusTimeOfAddition OBJECT-TYPE
   SYNTAX      DisplayString
   MAX-ACCESS  read-only
   STATUS      current
   DESCRIPTION
       " "
   ::= { opmen99810bPortSecPortStatusEntry 5 }

opmen99810bPortSecPortStatusAgeAndHold OBJECT-TYPE
   SYNTAX      DisplayString
   MAX-ACCESS  read-only
   STATUS      current
   DESCRIPTION
       " "
   ::= { opmen99810bPortSecPortStatusEntry 6 }


opmen99810bAccessManagement                                      OBJECT IDENTIFIER ::= { opmen99810bSecurity 6 }

opmen99810bAccessMgtConf                                         OBJECT IDENTIFIER ::= { opmen99810bAccessManagement 1 }

opmen99810bAccessMgtConfMode OBJECT-TYPE
   SYNTAX      INTEGER { disable(0), enable(1) }
   MAX-ACCESS  read-write
   STATUS      current
   DESCRIPTION
       "default: 0
       0: disable
       1: enable "
   ::= { opmen99810bAccessMgtConf 1 }

opmen99810bAccessMgtConfCreate OBJECT-TYPE
   SYNTAX      INTEGER { none(0), create(1) }
   MAX-ACCESS  read-write
   STATUS      current
   DESCRIPTION
       "default: 0
       0: none
       1: create "
   ::= { opmen99810bAccessMgtConf 2 }

opmen99810bAccessMgtConfTable OBJECT-TYPE
   SYNTAX      SEQUENCE OF Opmen99810bAccessMgtConfEntry
   MAX-ACCESS  not-accessible
   STATUS      current
   DESCRIPTION
       " "
   ::= { opmen99810bAccessMgtConf 3 }

opmen99810bAccessMgtConfEntry OBJECT-TYPE
   SYNTAX      Opmen99810bAccessMgtConfEntry
   MAX-ACCESS  not-accessible
   STATUS      current
   DESCRIPTION
       ""
   INDEX    { opmen99810bAccessMgtIndex  }
   ::= { opmen99810bAccessMgtConfTable 1 }

Opmen99810bAccessMgtConfEntry ::= SEQUENCE {
   opmen99810bAccessMgtIndex             Integer32,
   opmen99810bAccessMgtAddresstype       INTEGER,
   opmen99810bAccessMgtStartIpAddress    DisplayString,
   opmen99810bAccessMgtEndIpAddress      DisplayString,
   opmen99810bAccessMgtHttpHttps         INTEGER,
   opmen99810bAccessMgtSNMP              INTEGER,
   opmen99810bAccessMgtTelnetSSH         INTEGER,
   opmen99810bAccessMgtRowStatus         INTEGER
}

opmen99810bAccessMgtIndex OBJECT-TYPE
   SYNTAX      Integer32(1..16)
   MAX-ACCESS  read-write
   STATUS      current
   DESCRIPTION
       "Set Access Management config index
        range : 1-16."
   ::= { opmen99810bAccessMgtConfEntry 1 }

opmen99810bAccessMgtAddresstype OBJECT-TYPE
   SYNTAX      INTEGER { ipv4(0), ipv6(1) }
   MAX-ACCESS  read-write
   STATUS      current
   DESCRIPTION
       "0: ipv4
        1: ipv6 "
   ::= { opmen99810bAccessMgtConfEntry 2 }

opmen99810bAccessMgtStartIpAddress OBJECT-TYPE
   SYNTAX      DisplayString
   MAX-ACCESS  read-write
   STATUS      current
   DESCRIPTION
       " Start IP address.
         IP address doesn't allowed all zero or all 'ff'H."
   ::= { opmen99810bAccessMgtConfEntry 3 }

opmen99810bAccessMgtEndIpAddress OBJECT-TYPE
   SYNTAX      DisplayString
   MAX-ACCESS  read-write
   STATUS      current
   DESCRIPTION
       " End IP address.
         IP address doesn't allowed all zero or all 'ff'H.
         End ip address is not less than start ip address."
   ::= { opmen99810bAccessMgtConfEntry 4 }

opmen99810bAccessMgtHttpHttps OBJECT-TYPE
   SYNTAX      INTEGER { disable(0), enable(1) }
   MAX-ACCESS  read-write
   STATUS      current
   DESCRIPTION
       "default: 0
       0: disable
       1: enable "
   ::= { opmen99810bAccessMgtConfEntry 5 }

opmen99810bAccessMgtSNMP OBJECT-TYPE
   SYNTAX      INTEGER { disable(0), enable(1) }
   MAX-ACCESS  read-write
   STATUS      current
   DESCRIPTION
       "default: 0
       0: disable
       1: enable "
   ::= { opmen99810bAccessMgtConfEntry 6 }

opmen99810bAccessMgtTelnetSSH OBJECT-TYPE
   SYNTAX      INTEGER { disable(0), enable(1) }
   MAX-ACCESS  read-write
   STATUS      current
   DESCRIPTION
       "default: 0
       0: disable
       1: enable "
   ::= { opmen99810bAccessMgtConfEntry 7 }

opmen99810bAccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { opmen99810bAccessMgtConfEntry 8 }

opmen99810bAccessMgtStatistics                                   OBJECT IDENTIFIER ::= { opmen99810bAccessManagement 2 }

opmen99810bHttpReceivedPkts OBJECT-TYPE
   SYNTAX      Counter32
   MAX-ACCESS  read-only
   STATUS      current
   DESCRIPTION
       " "
   ::= { opmen99810bAccessMgtStatistics 1 }

opmen99810bHttpAllowedPkts OBJECT-TYPE
   SYNTAX      Counter32
   MAX-ACCESS  read-only
   STATUS      current
   DESCRIPTION
       " "
   ::= { opmen99810bAccessMgtStatistics 2 }

opmen99810bHttpDiscardedPkts OBJECT-TYPE
   SYNTAX      Counter32
   MAX-ACCESS  read-only
   STATUS      current
   DESCRIPTION
       " "
   ::= { opmen99810bAccessMgtStatistics 3 }

opmen99810bHttpsReceivedPkts OBJECT-TYPE
   SYNTAX      Counter32
   MAX-ACCESS  read-only
   STATUS      current
   DESCRIPTION
       " "
   ::= { opmen99810bAccessMgtStatistics 4 }

opmen99810bHttpsAllowedPkts OBJECT-TYPE
   SYNTAX      Counter32
   MAX-ACCESS  read-only
   STATUS      current
   DESCRIPTION
       " "
   ::= { opmen99810bAccessMgtStatistics 5 }

opmen99810bHttpsDiscardedPkts OBJECT-TYPE
   SYNTAX      Counter32
   MAX-ACCESS  read-only
   STATUS      current
   DESCRIPTION
       " "
   ::= { opmen99810bAccessMgtStatistics 6 }

opmen99810bSnmpReceivedPkts OBJECT-TYPE
   SYNTAX      Counter32
   MAX-ACCESS  read-only
   STATUS      current
   DESCRIPTION
       " "
   ::= { opmen99810bAccessMgtStatistics 7 }

opmen99810bSnmpAllowedPkts OBJECT-TYPE
   SYNTAX      Counter32
   MAX-ACCESS  read-only
   STATUS      current
   DESCRIPTION
       " "
   ::= { opmen99810bAccessMgtStatistics 8 }

opmen99810bSnmpDiscardedPkts OBJECT-TYPE
   SYNTAX      Counter32
   MAX-ACCESS  read-only
   STATUS      current
   DESCRIPTION
       " "
   ::= { opmen99810bAccessMgtStatistics 9 }

opmen99810bTelnetReceivedPkts OBJECT-TYPE
   SYNTAX      Counter32
   MAX-ACCESS  read-only
   STATUS      current
   DESCRIPTION
       " "
   ::= { opmen99810bAccessMgtStatistics 10 }

opmen99810bTelnetAllowedPkts OBJECT-TYPE
   SYNTAX      Counter32
   MAX-ACCESS  read-only
   STATUS      current
   DESCRIPTION
       " "
   ::= { opmen99810bAccessMgtStatistics 11 }

opmen99810bTelnetDiscardedPkts OBJECT-TYPE
   SYNTAX      Counter32
   MAX-ACCESS  read-only
   STATUS      current
   DESCRIPTION
       " "
   ::= { opmen99810bAccessMgtStatistics 12 }

opmen99810bSSHReceivedPkts OBJECT-TYPE
   SYNTAX      Counter32
   MAX-ACCESS  read-only
   STATUS      current
   DESCRIPTION
       " "
   ::= { opmen99810bAccessMgtStatistics 13 }

opmen99810bSSHAllowedPkts OBJECT-TYPE
   SYNTAX      Counter32
   MAX-ACCESS  read-only
   STATUS      current
   DESCRIPTION
       " "
   ::= { opmen99810bAccessMgtStatistics 14 }

opmen99810bSSHDiscardedPkts OBJECT-TYPE
   SYNTAX      Counter32
   MAX-ACCESS  read-only
   STATUS      current
   DESCRIPTION
       " "
   ::= { opmen99810bAccessMgtStatistics 15 }

opmen99810bAccessMgtStatisticsClearAll OBJECT-TYPE
   SYNTAX      INTEGER { none(0), clear(1) }
   MAX-ACCESS  read-write
   STATUS      current
   DESCRIPTION
       "0: none
        1: clear"
   ::= { opmen99810bAccessMgtStatistics 16 }

opmen99810bSSH                                                   OBJECT IDENTIFIER ::= { opmen99810bSecurity 7 }

opmen99810bSSHMode OBJECT-TYPE
   SYNTAX      INTEGER { disable(0), enable(1) }
   MAX-ACCESS  read-write
   STATUS      current
   DESCRIPTION
       "default: 1
        0: disable
        1: enable"
   ::= { opmen99810bSSH 1 }

opmen99810bHTTPS                                                 OBJECT IDENTIFIER ::= { opmen99810bSecurity 8 }

opmen99810bHTTPSMode OBJECT-TYPE
   SYNTAX      INTEGER { disable(0), enable(1) }
   MAX-ACCESS  read-write
   STATUS      current
   DESCRIPTION
       "default: 1
        0: disable
        1: enable"
   ::= { opmen99810bHTTPS 1 }

opmen99810bHTTPSAutoRedirect OBJECT-TYPE
   SYNTAX      INTEGER { disable(0), enable(1) }
   MAX-ACCESS  read-write
   STATUS      current
   DESCRIPTION
       "default: 0
        0: disable
        1: enable"
   ::= { opmen99810bHTTPS 2 }

opmen99810bAuthMethod                                            OBJECT IDENTIFIER ::= { opmen99810bSecurity 9 }

opmen99810bConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { opmen99810bAuthMethod 1 }

opmen99810bConsoleFallback OBJECT-TYPE
   SYNTAX      INTEGER { disable(0), enable(1) }
   MAX-ACCESS  read-write
   STATUS      current
   DESCRIPTION
       "default: 0
        0:disable
        1:enable"
   ::= { opmen99810bAuthMethod 2 }

opmen99810bTelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { opmen99810bAuthMethod 3 }

opmen99810bTelnetFallback OBJECT-TYPE
   SYNTAX      INTEGER { disable(0), enable(1) }
   MAX-ACCESS  read-write
   STATUS      current
   DESCRIPTION
       "default: 0
        0:disable
        1:enable"
   ::= { opmen99810bAuthMethod 4 }

opmen99810bSshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { opmen99810bAuthMethod 5 }

opmen99810bSshFallback OBJECT-TYPE
   SYNTAX      INTEGER { disable(0), enable(1) }
   MAX-ACCESS  read-write
   STATUS      current
   DESCRIPTION
       "default: 0
        0:disable
        1:enable"
   ::= { opmen99810bAuthMethod 6 }

opmen99810bWebAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { opmen99810bAuthMethod 7 }

opmen99810bWebFallback OBJECT-TYPE
   SYNTAX      INTEGER { disable(0), enable(1) }
   MAX-ACCESS  read-write
   STATUS      current
   DESCRIPTION
       "default: 0
        0:disable
        1:enable"
   ::= { opmen99810bAuthMethod 8 }

opmen99810bMaintenance                                           OBJECT IDENTIFIER ::= { opmen99810bProductId 4 }

opmen99810bRestartDevice OBJECT-TYPE
   SYNTAX      INTEGER { disable(0), enable(1) }
   MAX-ACCESS  read-write
   STATUS      current
   DESCRIPTION
       "default: 0
        0:none
        1:yes"
   ::= { opmen99810bMaintenance 1 }

opmen99810bFirmware                                         OBJECT IDENTIFIER ::= { opmen99810bMaintenance 2 }

opmen99810bFirmwareIpAddress OBJECT-TYPE
   SYNTAX       IpAddress
   MAX-ACCESS   read-write
   STATUS       current
   DESCRIPTION
        "Get/Set the firmware tftp server."
   ::= { opmen99810bFirmware 1 }

opmen99810bFirmwareFileName OBJECT-TYPE
   SYNTAX       DisplayString
   MAX-ACCESS   read-write
   STATUS       current
   DESCRIPTION
        "Get/Set the path and filename for firmware upgrading."
   ::= { opmen99810bFirmware 2 }

opmen99810bDoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { opmen99810bFirmware 3 }

opmen99810bSaveOrRestore                                         OBJECT IDENTIFIER ::= { opmen99810bMaintenance 3 }

opmen99810bFactoryDefaults OBJECT-TYPE
   SYNTAX      INTEGER { none(0), yes(1) }
   MAX-ACCESS  read-write
   STATUS      current
   DESCRIPTION
       "default: 0
        0:none
        1:yes"
   ::= { opmen99810bSaveOrRestore 1 }

opmen99810bSaveStart OBJECT-TYPE
   SYNTAX      INTEGER { none(0), yes(1) }
   MAX-ACCESS  read-write
   STATUS      current
   DESCRIPTION
       "default: 0
        0:none
        1:yes"
   ::= { opmen99810bSaveOrRestore 2 }

opmen99810bSaveUser OBJECT-TYPE
   SYNTAX      INTEGER { none(0), yes(1) }
   MAX-ACCESS  read-write
   STATUS      current
   DESCRIPTION
       "default: 0
        0:none
        1:yes"
   ::= { opmen99810bSaveOrRestore 3 }

opmen99810bRestoreUser OBJECT-TYPE
   SYNTAX      INTEGER { none(0), yes(1) }
   MAX-ACCESS  read-write
   STATUS      current
   DESCRIPTION
       "default: 0
        0:none
        1:yes"
   ::= { opmen99810bSaveOrRestore 4 }


opmen99810bExportOrImport                                        OBJECT IDENTIFIER ::= { opmen99810bMaintenance 4 }

opmen99810bExportIpAddress OBJECT-TYPE
   SYNTAX       IpAddress
   MAX-ACCESS   read-write
   STATUS       current
   DESCRIPTION
        "Get/Set the export tftp server."
   ::= { opmen99810bExportOrImport 1 }

opmen99810bExportConfigName OBJECT-TYPE
   SYNTAX       DisplayString
   MAX-ACCESS   read-write
   STATUS       current
   DESCRIPTION
       "Get/Set the export file path and name."
   ::= { opmen99810bExportOrImport 2 }

opmen99810bDoExportConfig OBJECT-TYPE
   SYNTAX       INTEGER{ doNothing(0), do(1) }
   MAX-ACCESS   read-write
   STATUS       current
   DESCRIPTION
        "Do export-config.
         Get this OID always return zero.
         1 - export."
   ::= { opmen99810bExportOrImport 3 }

opmen99810bImportIpAddress OBJECT-TYPE
   SYNTAX       IpAddress
   MAX-ACCESS   read-write
   STATUS       current
   DESCRIPTION
        "Get/Set the import tftp server."
   ::= { opmen99810bExportOrImport 4 }

opmen99810bImportConfigName OBJECT-TYPE
   SYNTAX      DisplayString
   MAX-ACCESS  read-write
   STATUS      current
   DESCRIPTION
       "Get/Set the import file path and name."
   ::= { opmen99810bExportOrImport 5 }

opmen99810bDoImportConfig OBJECT-TYPE
   SYNTAX       INTEGER{ doNothing(0), do(1) }
   MAX-ACCESS   read-write
   STATUS       current
   DESCRIPTION
        "Do export-config.
         Get this OID always return zero.
         1 - import."
   ::= { opmen99810bExportOrImport 6 }

opmen99810bDiagnostics                                           OBJECT IDENTIFIER ::= { opmen99810bMaintenance 5 }

opmen99810bPingIpAddress OBJECT-TYPE
   SYNTAX      IpAddress
   MAX-ACCESS  read-write
   STATUS      current
   DESCRIPTION
       " The destination IP Address. "
   ::= { opmen99810bDiagnostics 1 }

opmen99810bPingSize OBJECT-TYPE
   SYNTAX      Integer32(60..1400)
   MAX-ACCESS  read-write
   STATUS      current
   DESCRIPTION
       " Size of ICMP echo packet.
         range : 60-1400, default : 64. "
   ::= { opmen99810bDiagnostics 2 }

opmen99810bDoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { opmen99810bDiagnostics 3 }

opmen99810bPingResult OBJECT-TYPE
   SYNTAX      DisplayString
   MAX-ACCESS  read-only
   STATUS      current
   DESCRIPTION
       " Show ping result. "
   ::= { opmen99810bDiagnostics 4 }

opmen99810bPing6IpAddress OBJECT-TYPE
   SYNTAX      DisplayString
   MAX-ACCESS  read-write
   STATUS      current
   DESCRIPTION
       " The destination IPv6 Address. "
   ::= { opmen99810bDiagnostics 5 }

opmen99810bPing6Size OBJECT-TYPE
   SYNTAX      Integer32(60..1400)
   MAX-ACCESS  read-write
   STATUS      current
   DESCRIPTION
       " Size of ICMP echo packet.
         range : 60-1400. "
   ::= { opmen99810bDiagnostics 6 }

opmen99810bDoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { opmen99810bDiagnostics 7 }

opmen99810bPing6Result OBJECT-TYPE
   SYNTAX      DisplayString
   MAX-ACCESS  read-only
   STATUS      current
   DESCRIPTION
       " Show ping result. "
   ::= { opmen99810bDiagnostics 8 }




------------------------------------------------------------------------------------------------------------------
opmen99810bTrap                                                  OBJECT IDENTIFIER ::= { opmen99810bProductId 5 }

opmen99810bTrapEvent                                             OBJECT IDENTIFIER ::= { opmen99810bTrap 1 }

opmen99810bEmergency NOTIFICATION-TYPE
  OBJECTS   { opmen99810bInformation }
  STATUS        current
    DESCRIPTION
        "The severity level is Emergency. The system is unusable."
    ::= { opmen99810bTrapEvent 1 }

opmen99810bAlert NOTIFICATION-TYPE
  OBJECTS   { opmen99810bInformation }
  STATUS        current
    DESCRIPTION
        "The severity level is Alert. The action must be taken immediately."
    ::= { opmen99810bTrapEvent 2 }

opmen99810bCritical NOTIFICATION-TYPE
  OBJECTS   { opmen99810bInformation }
  STATUS        current
    DESCRIPTION
        "The severity level is Critical. Critical conditions."
    ::= { opmen99810bTrapEvent 3 }

opmen99810bError NOTIFICATION-TYPE
  OBJECTS   { opmen99810bInformation }
  STATUS        current
    DESCRIPTION
        "The severity level is Error. Error conditions."
    ::= { opmen99810bTrapEvent 4 }

opmen99810bWarning NOTIFICATION-TYPE
  OBJECTS   { opmen99810bInformation }
  STATUS        current
    DESCRIPTION
        "The severity level is Warning. Warning conditions."
    ::= { opmen99810bTrapEvent 5 }

opmen99810bNotice NOTIFICATION-TYPE
  OBJECTS   { opmen99810bInformation }
  STATUS        current
    DESCRIPTION
        "The severity level is Notice. Normal but significant condition."
    ::= { opmen99810bTrapEvent 6 }

opmen99810bInformational NOTIFICATION-TYPE
  OBJECTS   { opmen99810bInformation }
  STATUS        current
    DESCRIPTION
        "The severity level is Informational. Informational messages."
    ::= { opmen99810bTrapEvent 7 }

opmen99810bDebug NOTIFICATION-TYPE
  OBJECTS   { opmen99810bInformation }
  STATUS        current
    DESCRIPTION
        "The severity level is Debug. debug-level messages."
    ::= { opmen99810bTrapEvent 8 }

opmen99810bTrapVariable                                          OBJECT IDENTIFIER ::= { opmen99810bTrap 2 }

opmen99810bInformation OBJECT-TYPE
    SYNTAX      DisplayString
    MAX-ACCESS  read-only
    STATUS      current
    DESCRIPTION
        "Trap information."
    ::= { opmen99810bTrapVariable 1 }


END
