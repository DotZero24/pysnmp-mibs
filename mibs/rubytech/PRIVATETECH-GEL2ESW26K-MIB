PRIVATETECH-GEL2ESW26K-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

privatetech MODULE-IDENTITY
        LAST-UPDATED "201301230000Z"
        ORGANIZATION "Corp."
        CONTACT-INFO
            ""
        DESCRIPTION
            ""
        ::= { enterprises 5205 }

switch                                                          OBJECT IDENTIFIER ::= { privatetech 2 }

gel2esw26kProductId                                             OBJECT IDENTIFIER ::= { switch 54 }

gel2esw26kSystem                                                OBJECT IDENTIFIER ::= { gel2esw26kProductId 1 }

gel2esw26kSystemInformation                                     OBJECT IDENTIFIER ::= { gel2esw26kSystem 1 }

gel2esw26kModelName OBJECT-TYPE
   SYNTAX       DisplayString
   MAX-ACCESS   read-only
   STATUS       current
   DESCRIPTION
       ""
 ::= { gel2esw26kSystemInformation 1 }

gel2esw26kBIOSVersion OBJECT-TYPE
   SYNTAX       DisplayString
   MAX-ACCESS   read-only
   STATUS       current
   DESCRIPTION
       ""
   ::= { gel2esw26kSystemInformation 2 }

gel2esw26kFirmwareVersion OBJECT-TYPE
   SYNTAX       DisplayString
   MAX-ACCESS   read-only
   STATUS       current
   DESCRIPTION
       ""
   ::= { gel2esw26kSystemInformation 3 }

gel2esw26kHardwareMechanicalVersion OBJECT-TYPE
   SYNTAX       DisplayString
   MAX-ACCESS   read-only
   STATUS       current
   DESCRIPTION
       ""
   ::= { gel2esw26kSystemInformation 4 }

gel2esw26kSeriesNumber OBJECT-TYPE
   SYNTAX       DisplayString
   MAX-ACCESS   read-only
   STATUS       current
   DESCRIPTION
       ""
   ::= { gel2esw26kSystemInformation 5 }

gel2esw26kHostMACAddress OBJECT-TYPE
   SYNTAX       MacAddress
   MAX-ACCESS   read-only
   STATUS       current
   DESCRIPTION
       ""
   ::= { gel2esw26kSystemInformation 6 }

gel2esw26kConsoleBaudrate OBJECT-TYPE
   SYNTAX       DisplayString
   MAX-ACCESS   read-only
   STATUS       current
   DESCRIPTION
       ""
   ::= { gel2esw26kSystemInformation 7 }

gel2esw26kRAMSize OBJECT-TYPE
   SYNTAX       DisplayString
   MAX-ACCESS   read-only
   STATUS       current
   DESCRIPTION
       ""
   ::= { gel2esw26kSystemInformation 8 }

gel2esw26kFlashSize OBJECT-TYPE
   SYNTAX       DisplayString
   MAX-ACCESS   read-only
   STATUS       current
   DESCRIPTION
       ""
   ::= { gel2esw26kSystemInformation 9 }

gel2esw26kBridgeFBDSize OBJECT-TYPE
   SYNTAX       DisplayString
   MAX-ACCESS   read-only
   STATUS       current
   DESCRIPTION
       ""
   ::= { gel2esw26kSystemInformation 10 }

gel2esw26kTransmitQueue OBJECT-TYPE
   SYNTAX       DisplayString
   MAX-ACCESS   read-only
   STATUS       current
   DESCRIPTION
       ""
   ::= { gel2esw26kSystemInformation 11 }

gel2esw26kMaximumFrameSize OBJECT-TYPE
   SYNTAX       DisplayString
   MAX-ACCESS   read-only
   STATUS       current
   DESCRIPTION
       ""
   ::= { gel2esw26kSystemInformation 12 }

gel2esw26kCPULoad OBJECT-TYPE
   SYNTAX       DisplayString
   MAX-ACCESS   read-only
   STATUS       current
   DESCRIPTION
       ""
   ::= { gel2esw26kSystemInformation 13 }


gel2esw26kSystemTime                                            OBJECT IDENTIFIER ::= { gel2esw26kSystem 2 }

gel2esw26kSystemTimeManual                                      OBJECT IDENTIFIER ::= { gel2esw26kSystemTime 1 }

gel2esw26kSystemTimeManualClockSource OBJECT-TYPE
   SYNTAX       INTEGER(0|1)
   MAX-ACCESS   read-write
   STATUS       current
   DESCRIPTION
       "default: 0,
        0 : Use Local Settings,
        1 : Use NTP Server."
   ::= { gel2esw26kSystemTimeManual 1 }

gel2esw26kSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gel2esw26kSystemTimeManual 2 }

gel2esw26kSystemTimeManualTimeZoneOffset OBJECT-TYPE
   SYNTAX       INTEGER(-720..780)
   MAX-ACCESS   read-write
   STATUS       current
   DESCRIPTION
       "Get/Set the NTP Time Zone.
        The value range is between -720 and 780 (minutes)."
   ::= { gel2esw26kSystemTimeManual 3 }

gel2esw26kSystemTimeManualDaylightSavings OBJECT-TYPE
   SYNTAX       INTEGER(0|1)
   MAX-ACCESS   read-write
   STATUS       current
   DESCRIPTION
       "default: 0,
        0 : Disable,
        1 : Enable."
   ::= { gel2esw26kSystemTimeManual 4 }

gel2esw26kSystemTimeManualTimeSetOffset OBJECT-TYPE
   SYNTAX       INTEGER(1..1440)
   MAX-ACCESS   read-write
   STATUS       current
   DESCRIPTION
       "Get/Set the Daylight Saving Time.
        The value range is between 1 and 1440 (minutes),
        Default : 60 (minutes)."
   ::= { gel2esw26kSystemTimeManual 5 }

gel2esw26kSystemTimeManualDaylightSavingsType OBJECT-TYPE
   SYNTAX       INTEGER(0|1)
   MAX-ACCESS   read-write
   STATUS       current
   DESCRIPTION
       "default: 0,
        0 : By dates,
        1 : Recurring."
   ::= { gel2esw26kSystemTimeManual 6 }

gel2esw26kSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gel2esw26kSystemTimeManual 7 }

gel2esw26kSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gel2esw26kSystemTimeManual 8 }

gel2esw26kSystemTimeManualDaylightSavingsRecurringDayFrom OBJECT-TYPE
   SYNTAX       INTEGER(0..6)
   MAX-ACCESS   read-write
   STATUS       current
   DESCRIPTION
       "Get/Set the Daylight Saving Time Day From.
        0 : Sun, 1 : Mon, 2 : Tue, 3 : Wed, 4 : Thu, 5 : Fri, 6 : Sat."
   ::= { gel2esw26kSystemTimeManual 9 }

gel2esw26kSystemTimeManualDaylightSavingsRecurringWeekFrom OBJECT-TYPE
   SYNTAX       INTEGER(1..5)
   MAX-ACCESS   read-write
   STATUS       current
   DESCRIPTION
       "Get/Set the Daylight Saving Time Week From.
        1 : first week, 2, 3, 4, 5 : last week"
   ::= { gel2esw26kSystemTimeManual 10 }

gel2esw26kSystemTimeManualDaylightSavingsRecurringMonthFrom OBJECT-TYPE
   SYNTAX       INTEGER(0..11)
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gel2esw26kSystemTimeManual 11 }

gel2esw26kSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gel2esw26kSystemTimeManual 12 }

gel2esw26kSystemTimeManualDaylightSavingsRecurringDayTo OBJECT-TYPE
   SYNTAX       INTEGER(0..6)
   MAX-ACCESS   read-write
   STATUS       current
   DESCRIPTION
       "Get/Set the Daylight Saving Time Day To.
        0 : Sun, 1 : Mon, 2 : Tue, 3 : Wed, 4 : Thu, 5 : Fri, 6 : Sat."
   ::= { gel2esw26kSystemTimeManual 13 }

gel2esw26kSystemTimeManualDaylightSavingsRecurringWeekTo OBJECT-TYPE
   SYNTAX       INTEGER(1..5)
   MAX-ACCESS   read-write
   STATUS       current
   DESCRIPTION
       "Get/Set the Daylight Saving Time Week To.
        1 : first week, 2, 3, 4, 5 : last week"
   ::= { gel2esw26kSystemTimeManual 14 }

gel2esw26kSystemTimeManualDaylightSavingsRecurringMonthTo OBJECT-TYPE
   SYNTAX       INTEGER(0..11)
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gel2esw26kSystemTimeManual 15 }

gel2esw26kSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gel2esw26kSystemTimeManual 16 }

gel2esw26kSystemTimeNTP                                     OBJECT IDENTIFIER ::= { gel2esw26kSystemTime 2 }

gel2esw26kSystemTimeNTPTable OBJECT-TYPE
   SYNTAX      SEQUENCE OF GEL2ESW26KSystemTimeNTPEntry
   MAX-ACCESS  not-accessible
   STATUS      current
   DESCRIPTION
       " "
   ::= { gel2esw26kSystemTimeNTP 1 }

gel2esw26kSystemTimeNTPEntry OBJECT-TYPE
   SYNTAX      GEL2ESW26KSystemTimeNTPEntry
   MAX-ACCESS  not-accessible
   STATUS      current
   DESCRIPTION
       ""
   INDEX    { gel2esw26kSystemTimeNTPIndex  }
   ::= { gel2esw26kSystemTimeNTPTable 1 }

GEL2ESW26KSystemTimeNTPEntry ::= SEQUENCE {
   gel2esw26kSystemTimeNTPIndex             INTEGER,
   gel2esw26kSystemTimeNTPServerIPType      INTEGER,
   gel2esw26kSystemTimeNTPServer            DisplayString,
   gel2esw26kSystemTimeNTPCurrentMode       INTEGER
}

gel2esw26kSystemTimeNTPIndex OBJECT-TYPE
   SYNTAX      INTEGER (1..5)
   MAX-ACCESS  not-accessible
   STATUS      current
   DESCRIPTION
       " The index of the ntp entry. "
   ::= { gel2esw26kSystemTimeNTPEntry 1 }

gel2esw26kSystemTimeNTPServerIPType OBJECT-TYPE
   SYNTAX       INTEGER(0|1)
   MAX-ACCESS   read-write
   STATUS       current
   DESCRIPTION
       "Default: 0,
        0 : IPv4,
        1 : IPv6."
   ::= { gel2esw26kSystemTimeNTPEntry 2 }

gel2esw26kSystemTimeNTPServer OBJECT-TYPE
   SYNTAX       DisplayString
   MAX-ACCESS   read-write
   STATUS       current
   DESCRIPTION
       "Get/Set the NTP Time Server1. You can use the IP address or domain name."
   ::= { gel2esw26kSystemTimeNTPEntry 3 }

gel2esw26kSystemTimeNTPCurrentMode OBJECT-TYPE
   SYNTAX      INTEGER (0..3)
   MAX-ACCESS  read-write
   STATUS      current
   DESCRIPTION
       " 0: Empty
        1: Active
        2: Edit
        3: Delete"
   ::= { gel2esw26kSystemTimeNTPEntry 4 }


gel2esw26kSystemAccount                                         OBJECT IDENTIFIER ::= { gel2esw26kSystem 3 }

gel2esw26kSystemAccountUsers                                    OBJECT IDENTIFIER ::= { gel2esw26kSystemAccount 1 }

gel2esw26kSystemAccountUserCreate OBJECT-TYPE
   SYNTAX       INTEGER(0|1)
   MAX-ACCESS   read-write
   STATUS       current
   DESCRIPTION
       "default: 0
        0 : None  (read only)
        1 : Create a user account"
   ::= { gel2esw26kSystemAccountUsers 1 }

gel2esw26kSystemAccountUsersTable OBJECT-TYPE
   SYNTAX      SEQUENCE OF GEL2ESW26KSystemAccountUsersEntry
   MAX-ACCESS  not-accessible
   STATUS      current
   DESCRIPTION
       " "
   ::= { gel2esw26kSystemAccountUsers 2 }

gel2esw26kSystemAccountUsersEntry OBJECT-TYPE
   SYNTAX      GEL2ESW26KSystemAccountUsersEntry
   MAX-ACCESS  not-accessible
   STATUS      current
   DESCRIPTION
       ""
   INDEX    { gel2esw26kUserIndex  }
   ::= { gel2esw26kSystemAccountUsersTable 1 }


GEL2ESW26KSystemAccountUsersEntry ::= SEQUENCE {
   gel2esw26kUserIndex              INTEGER,
   gel2esw26kUserName               DisplayString,
   gel2esw26kPassword               DisplayString,
   gel2esw26kUserPrivilegeLevel     INTEGER,
   gel2esw26kAccountUserRowStatus   INTEGER
}


gel2esw26kUserIndex OBJECT-TYPE
   SYNTAX      INTEGER (1..20)
   MAX-ACCESS  not-accessible
   STATUS      current
   DESCRIPTION
       " "
   ::= { gel2esw26kSystemAccountUsersEntry 1 }

gel2esw26kUserName OBJECT-TYPE
   SYNTAX      DisplayString (SIZE (1..32))
   MAX-ACCESS  read-write
   STATUS      current
   DESCRIPTION
       " "
   ::= { gel2esw26kSystemAccountUsersEntry 2 }

gel2esw26kPassword OBJECT-TYPE
   SYNTAX      DisplayString (SIZE (1..32))
   MAX-ACCESS  read-write
   STATUS      current
   DESCRIPTION
       " "
   ::= { gel2esw26kSystemAccountUsersEntry 3 }

gel2esw26kUserPrivilegeLevel OBJECT-TYPE
   SYNTAX      INTEGER (1..15)
   MAX-ACCESS  read-write
   STATUS      current
   DESCRIPTION
       "default:1
        User privilege level range : 1 - 15"
   ::= { gel2esw26kSystemAccountUsersEntry 4 }

gel2esw26kAccountUserRowStatus OBJECT-TYPE
   SYNTAX      INTEGER (1..5)
   MAX-ACCESS  read-write
   STATUS      current
   DESCRIPTION
       " 1: active
        2: notInservice
        3: edit
        4: destroy
        5: undo"
   ::= { gel2esw26kSystemAccountUsersEntry 5 }

gel2esw26kSystemAccountPrivilegeLevel                           OBJECT IDENTIFIER ::= { gel2esw26kSystemAccount 2 }

gel2esw26kAccountPrivilegeLevel OBJECT-TYPE
   SYNTAX      INTEGER (1..15)
   MAX-ACCESS  read-write
   STATUS      current
   DESCRIPTION
       "Default:10, Range : 1-15. "
   ::= { gel2esw26kSystemAccountPrivilegeLevel 1 }

gel2esw26kAggregationPrivilegeLevel OBJECT-TYPE
   SYNTAX      INTEGER (1..15)
   MAX-ACCESS  read-write
   STATUS      current
   DESCRIPTION
       "Default:10, Range : 1-15. "
   ::= { gel2esw26kSystemAccountPrivilegeLevel 2 }

gel2esw26kDiagnosticsPrivilegeLevel OBJECT-TYPE
   SYNTAX      INTEGER (1..15)
   MAX-ACCESS  read-write
   STATUS      current
   DESCRIPTION
       "Default:10, Range : 1-15. "
   ::= { gel2esw26kSystemAccountPrivilegeLevel 3 }

gel2esw26kEEEPrivilegeLevel OBJECT-TYPE
   SYNTAX      INTEGER (1..15)
   MAX-ACCESS  read-write
   STATUS      current
   DESCRIPTION
       "Default:10, Range : 1-15. "
   ::= { gel2esw26kSystemAccountPrivilegeLevel 4 }

gel2esw26kEasyportPrivilegeLevel OBJECT-TYPE
   SYNTAX      INTEGER (1..15)
   MAX-ACCESS  read-write
   STATUS      current
   DESCRIPTION
       "Default:10, Range : 1-15. "
   ::= { gel2esw26kSystemAccountPrivilegeLevel 9 }

gel2esw26kGARPPrivilegeLevel OBJECT-TYPE
   SYNTAX      INTEGER (1..15)
   MAX-ACCESS  read-write
   STATUS      current
   DESCRIPTION
       "Default:10, Range : 1-15. "
   ::= { gel2esw26kSystemAccountPrivilegeLevel 10 }

gel2esw26kGVRPPrivilegeLevel OBJECT-TYPE
   SYNTAX      INTEGER (1..15)
   MAX-ACCESS  read-write
   STATUS      current
   DESCRIPTION
       "Default:10, Range : 1-15. "
   ::= { gel2esw26kSystemAccountPrivilegeLevel 11 }

gel2esw26kIPPrivilegeLevel OBJECT-TYPE
   SYNTAX      INTEGER (1..15)
   MAX-ACCESS  read-write
   STATUS      current
   DESCRIPTION
       "Default:10, Range : 1-15. "
   ::= { gel2esw26kSystemAccountPrivilegeLevel 12 }

gel2esw26kIPMCSnoopingPrivilegeLevel OBJECT-TYPE
   SYNTAX      INTEGER (1..15)
   MAX-ACCESS  read-write
   STATUS      current
   DESCRIPTION
       "Default:10, Range : 1-15. "
   ::= { gel2esw26kSystemAccountPrivilegeLevel 13 }

gel2esw26kLACPPrivilegeLevel OBJECT-TYPE
   SYNTAX      INTEGER (1..15)
   MAX-ACCESS  read-write
   STATUS      current
   DESCRIPTION
       "Default:10, Range : 1-15. "
   ::= { gel2esw26kSystemAccountPrivilegeLevel 14 }

gel2esw26kLLDPPrivilegeLevel OBJECT-TYPE
   SYNTAX      INTEGER (1..15)
   MAX-ACCESS  read-write
   STATUS      current
   DESCRIPTION
       "Default:10, Range : 1-15. "
   ::= { gel2esw26kSystemAccountPrivilegeLevel 15 }

gel2esw26kLLDPMEDPrivilegeLevel OBJECT-TYPE
   SYNTAX      INTEGER (1..15)
   MAX-ACCESS  read-write
   STATUS      current
   DESCRIPTION
       "Default:10, Range : 1-15. "
   ::= { gel2esw26kSystemAccountPrivilegeLevel 16 }

gel2esw26kLoopProtectPrivilegeLevel OBJECT-TYPE
   SYNTAX      INTEGER (1..15)
   MAX-ACCESS  read-write
   STATUS      current
   DESCRIPTION
       "Default:10, Range : 1-15. "
   ::= { gel2esw26kSystemAccountPrivilegeLevel 17 }

gel2esw26kMACTablePrivilegeLevel OBJECT-TYPE
   SYNTAX      INTEGER (1..15)
   MAX-ACCESS  read-write
   STATUS      current
   DESCRIPTION
       "Default:10, Range : 1-15. "
   ::= { gel2esw26kSystemAccountPrivilegeLevel 18 }

gel2esw26kMVRPrivilegeLevel OBJECT-TYPE
   SYNTAX      INTEGER (1..15)
   MAX-ACCESS  read-write
   STATUS      current
   DESCRIPTION
       "Default:10, Range : 1-15. "
   ::= { gel2esw26kSystemAccountPrivilegeLevel 22 }

gel2esw26kMaintenancePrivilegeLevel OBJECT-TYPE
   SYNTAX      INTEGER (1..15)
   MAX-ACCESS  read-write
   STATUS      current
   DESCRIPTION
       "Default:10, Range : 1-15. "
   ::= { gel2esw26kSystemAccountPrivilegeLevel 24 }

gel2esw26kMirroringPrivilegeLevel OBJECT-TYPE
   SYNTAX      INTEGER (1..15)
   MAX-ACCESS  read-write
   STATUS      current
   DESCRIPTION
       "Default:10, Range : 1-15. "
   ::= { gel2esw26kSystemAccountPrivilegeLevel 25 }

gel2esw26kPortsPrivilegeLevel OBJECT-TYPE
   SYNTAX      INTEGER (1..15)
   MAX-ACCESS  read-write
   STATUS      current
   DESCRIPTION
       "Default:10, Range : 1-15. "
   ::= { gel2esw26kSystemAccountPrivilegeLevel 27 }

gel2esw26kPrivateVLANsPrivilegeLevel OBJECT-TYPE
   SYNTAX      INTEGER (1..15)
   MAX-ACCESS  read-write
   STATUS      current
   DESCRIPTION
       "Default:10, Range : 1-15. "
   ::= { gel2esw26kSystemAccountPrivilegeLevel 28 }

gel2esw26kQoSPrivilegeLevel OBJECT-TYPE
   SYNTAX      INTEGER (1..15)
   MAX-ACCESS  read-write
   STATUS      current
   DESCRIPTION
       "Default:10, Range : 1-15. "
   ::= { gel2esw26kSystemAccountPrivilegeLevel 29 }

gel2esw26kSFlowPrivilegeLevel OBJECT-TYPE
   SYNTAX      INTEGER (1..15)
   MAX-ACCESS  read-write
   STATUS      current
   DESCRIPTION
       "Default:10, Range : 1-15. "
   ::= { gel2esw26kSystemAccountPrivilegeLevel 30 }

gel2esw26kSMTPPrivilegeLevel OBJECT-TYPE
   SYNTAX      INTEGER (1..15)
   MAX-ACCESS  read-write
   STATUS      current
   DESCRIPTION
       "Default:10, Range : 1-15. "
   ::= { gel2esw26kSystemAccountPrivilegeLevel 31 }

gel2esw26kSNMPPrivilegeLevel OBJECT-TYPE
   SYNTAX      INTEGER (1..15)
   MAX-ACCESS  read-write
   STATUS      current
   DESCRIPTION
       "Default:10, Range : 1-15. "
   ::= { gel2esw26kSystemAccountPrivilegeLevel 32 }

gel2esw26kSecurityPrivilegeLevel OBJECT-TYPE
   SYNTAX      INTEGER (1..15)
   MAX-ACCESS  read-write
   STATUS      current
   DESCRIPTION
       "Default:10, Range : 1-15. "
   ::= { gel2esw26kSystemAccountPrivilegeLevel 33 }

gel2esw26kSingleIPPrivilegeLevel OBJECT-TYPE
   SYNTAX      INTEGER (1..15)
   MAX-ACCESS  read-write
   STATUS      current
   DESCRIPTION
       "Default:10, Range : 1-15. "
   ::= { gel2esw26kSystemAccountPrivilegeLevel 34 }

gel2esw26kSpanningTreePrivilegeLevel OBJECT-TYPE
   SYNTAX      INTEGER (1..15)
   MAX-ACCESS  read-write
   STATUS      current
   DESCRIPTION
       "Default:10, Range : 1-15. "
   ::= { gel2esw26kSystemAccountPrivilegeLevel 35 }

gel2esw26kSystemPrivilegeLevel OBJECT-TYPE
   SYNTAX      INTEGER (1..15)
   MAX-ACCESS  read-write
   STATUS      current
   DESCRIPTION
       "Default:10, Range : 1-15. "
   ::= { gel2esw26kSystemAccountPrivilegeLevel 36 }

gel2esw26kTrapEventPrivilegeLevel OBJECT-TYPE
   SYNTAX      INTEGER (1..15)
   MAX-ACCESS  read-write
   STATUS      current
   DESCRIPTION
       "Default:10, Range : 1-15. "
   ::= { gel2esw26kSystemAccountPrivilegeLevel 37 }

gel2esw26kUPnPPrivilegeLevel OBJECT-TYPE
   SYNTAX      INTEGER (1..15)
   MAX-ACCESS  read-write
   STATUS      current
   DESCRIPTION
       "Default:10, Range : 1-15. "
   ::= { gel2esw26kSystemAccountPrivilegeLevel 38 }

gel2esw26kVCLPrivilegeLevel OBJECT-TYPE
   SYNTAX      INTEGER (1..15)
   MAX-ACCESS  read-write
   STATUS      current
   DESCRIPTION
       "Default:10, Range : 1-15. "
   ::= { gel2esw26kSystemAccountPrivilegeLevel 39 }

gel2esw26kVLANsPrivilegeLevel OBJECT-TYPE
   SYNTAX      INTEGER (1..15)
   MAX-ACCESS  read-write
   STATUS      current
   DESCRIPTION
       "Default:10, Range : 1-15. "
   ::= { gel2esw26kSystemAccountPrivilegeLevel 41 }

gel2esw26kVoiceVLANPrivilegeLevel OBJECT-TYPE
   SYNTAX      INTEGER (1..15)
   MAX-ACCESS  read-write
   STATUS      current
   DESCRIPTION
       "Default:10, Range : 1-15. "
   ::= { gel2esw26kSystemAccountPrivilegeLevel 42 }


gel2esw26kIP                                                    OBJECT IDENTIFIER ::= { gel2esw26kSystem 4 }

gel2esw26kIPv4                                                  OBJECT IDENTIFIER ::= { gel2esw26kIP 1 }

gel2esw26kIPv4Configured                                                  OBJECT IDENTIFIER ::= { gel2esw26kIPv4 1 }

gel2esw26kIpv4DHCPClient OBJECT-TYPE
   SYNTAX      INTEGER (0|1)
   MAX-ACCESS  read-write
   STATUS      current
   DESCRIPTION
       "default:0
       0: disable
       1: enable"
   ::= { gel2esw26kIPv4Configured 1 }

gel2esw26kIPv4Address OBJECT-TYPE
   SYNTAX      IpAddress
   MAX-ACCESS  read-write
   STATUS      current
   DESCRIPTION
       ""
   ::= { gel2esw26kIPv4Configured 2 }

gel2esw26kIPv4Mask OBJECT-TYPE
   SYNTAX      IpAddress
   MAX-ACCESS  read-write
   STATUS      current
   DESCRIPTION
       ""
   ::= { gel2esw26kIPv4Configured 3 }

gel2esw26kIPv4Gateway OBJECT-TYPE
   SYNTAX      IpAddress
   MAX-ACCESS  read-write
   STATUS      current
   DESCRIPTION
       ""
   ::= { gel2esw26kIPv4Configured 4 }

gel2esw26kIPv4VLANId OBJECT-TYPE
   SYNTAX      INTEGER (1..4094)
   MAX-ACCESS  read-write
   STATUS      current
   DESCRIPTION
       "default:1"
   ::= { gel2esw26kIPv4Configured 5 }

gel2esw26kIPv4DNSServer OBJECT-TYPE
   SYNTAX      IpAddress
   MAX-ACCESS  read-write
   STATUS      current
   DESCRIPTION
       ""
   ::= { gel2esw26kIPv4Configured 6 }

gel2esw26kIPv4DNSProxy OBJECT-TYPE
   SYNTAX      INTEGER (0|1)
   MAX-ACCESS  read-write
   STATUS      current
   DESCRIPTION
       " "
   ::= { gel2esw26kIPv4Configured 7 }

gel2esw26kIPv4Current                                                  OBJECT IDENTIFIER ::= { gel2esw26kIPv4 2 }

gel2esw26kIpv4CurrentDHCPClient OBJECT-TYPE
   SYNTAX      INTEGER (0|1)
   MAX-ACCESS  read-write
   STATUS      current
   DESCRIPTION
       "default:0
       0: none (for read)
       1: renew"
   ::= { gel2esw26kIPv4Current 1 }

gel2esw26kIPv4CurrentAddress OBJECT-TYPE
   SYNTAX      IpAddress
   MAX-ACCESS  read-only
   STATUS      current
   DESCRIPTION
       ""
   ::= { gel2esw26kIPv4Current 2 }

gel2esw26kIPv4CurrentMask OBJECT-TYPE
   SYNTAX      IpAddress
   MAX-ACCESS  read-only
   STATUS      current
   DESCRIPTION
       ""
   ::= { gel2esw26kIPv4Current 3 }

gel2esw26kIPv4CurrentGateway OBJECT-TYPE
   SYNTAX      IpAddress
   MAX-ACCESS  read-only
   STATUS      current
   DESCRIPTION
       ""
   ::= { gel2esw26kIPv4Current 4 }

gel2esw26kIPv4CurrentVLANId OBJECT-TYPE
   SYNTAX      INTEGER (1..4094)
   MAX-ACCESS  read-only
   STATUS      current
   DESCRIPTION
       "default:1"
   ::= { gel2esw26kIPv4Current 5 }

gel2esw26kIPv4CurrentDNSServer OBJECT-TYPE
   SYNTAX      IpAddress
   MAX-ACCESS  read-only
   STATUS      current
   DESCRIPTION
       ""
   ::= { gel2esw26kIPv4Current 6 }


gel2esw26kIPv6                                                  OBJECT IDENTIFIER ::= { gel2esw26kIP 2 }

gel2esw26kIPv6Configured                                                  OBJECT IDENTIFIER ::= { gel2esw26kIPv6 1 }

gel2esw26kIpv6AutoConfiguration OBJECT-TYPE
   SYNTAX      INTEGER (0|1)
   MAX-ACCESS  read-write
   STATUS      current
   DESCRIPTION
       "default:0
       0: disable
       1: enable"
   ::= { gel2esw26kIPv6Configured 1 }

gel2esw26kIpv6Address OBJECT-TYPE
   SYNTAX      DisplayString (SIZE (0..30))
   MAX-ACCESS  read-write
   STATUS      current
   DESCRIPTION
       ""
   ::= { gel2esw26kIPv6Configured 2 }

gel2esw26kIpv6Prefix OBJECT-TYPE
   SYNTAX      INTEGER (1..128)
   MAX-ACCESS  read-write
   STATUS      current
   DESCRIPTION
       "default: 96"
   ::= { gel2esw26kIPv6Configured 3 }

gel2esw26kIpv6Gateway OBJECT-TYPE
   SYNTAX      DisplayString (SIZE (0..30))
   MAX-ACCESS  read-write
   STATUS      current
   DESCRIPTION
       " "
   ::= { gel2esw26kIPv6Configured 4 }

gel2esw26kIPv6Current                                                  OBJECT IDENTIFIER ::= { gel2esw26kIPv6 2 }

gel2esw26kIpv6CurrentAutoConfiguration OBJECT-TYPE
   SYNTAX      INTEGER (0|1)
   MAX-ACCESS  read-only
   STATUS      current
   DESCRIPTION
       "default:0
       0: disable
       1: enable"
   ::= { gel2esw26kIPv6Current 1 }

gel2esw26kIpv6CurrentAddress OBJECT-TYPE
   SYNTAX      DisplayString (SIZE (0..30))
   MAX-ACCESS  read-only
   STATUS      current
   DESCRIPTION
       ""
   ::= { gel2esw26kIPv6Current 2 }


gel2esw26kIpv6CurrentLinkLocalAddress OBJECT-TYPE
   SYNTAX      DisplayString(SIZE (0..30))
   MAX-ACCESS  read-only
   STATUS      current
   DESCRIPTION
       ""
   ::= { gel2esw26kIPv6Current 3 }


gel2esw26kIpv6CurrentPrefix OBJECT-TYPE
   SYNTAX      INTEGER (1..128)
   MAX-ACCESS  read-only
   STATUS      current
   DESCRIPTION
       ""
   ::= { gel2esw26kIPv6Current 4 }

gel2esw26kIpv6CurrentGateway OBJECT-TYPE
   SYNTAX      DisplayString (SIZE (0..30))
   MAX-ACCESS  read-only
   STATUS      current
   DESCRIPTION
       " "
   ::= { gel2esw26kIPv6Current 5 }

gel2esw26kSyslog                                                OBJECT IDENTIFIER ::= { gel2esw26kSystem 5 }

gel2esw26kSyslogConf                                            OBJECT IDENTIFIER ::= { gel2esw26kSyslog 1 }

gel2esw26kServerMode OBJECT-TYPE
   SYNTAX      INTEGER (0|1)
   MAX-ACCESS  read-write
   STATUS      current
   DESCRIPTION
       "default: 0
       0: disable
       1: enable "
   ::= { gel2esw26kSyslogConf 1 }

gel2esw26kServerAddress1 OBJECT-TYPE
   SYNTAX      IpAddress
   MAX-ACCESS  read-write
   STATUS      current
   DESCRIPTION
       " "
   ::= { gel2esw26kSyslogConf 2 }

gel2esw26kServerAddress2 OBJECT-TYPE
   SYNTAX      IpAddress
   MAX-ACCESS  read-write
   STATUS      current
   DESCRIPTION
       " "
   ::= { gel2esw26kSyslogConf 3 }

gel2esw26kSyslogLevel OBJECT-TYPE
   SYNTAX      INTEGER(0..7)
   MAX-ACCESS  read-write
   STATUS      current
   DESCRIPTION
       "default: 6 (Info)
       0: Emergency
       1: Alert
       2: Critical
       3: Error
       4: Warning
       5: Notice
       6: Info
       7: Debug"
   ::= { gel2esw26kSyslogConf 4 }

gel2esw26kSyslogDetailedInfo                                    OBJECT IDENTIFIER ::= { gel2esw26kSyslog 2 }

gel2esw26kSyslogDetailedInfoClear OBJECT-TYPE
   SYNTAX      INTEGER(0|1)
   MAX-ACCESS  read-write
   STATUS      current
   DESCRIPTION
      "default: 0
       0 : None  (read only)
       1 : Clear Syslog"
   ::= { gel2esw26kSyslogDetailedInfo 1 }

gel2esw26kSyslogDetailedInfoTable OBJECT-TYPE
  SYNTAX      SEQUENCE OF GEL2ESW26KSyslogDetailedInfoEntry
  MAX-ACCESS  not-accessible
  STATUS      current
  DESCRIPTION
           " "
       ::= { gel2esw26kSyslogDetailedInfo 2 }

gel2esw26kSyslogDetailedInfoEntry OBJECT-TYPE
   SYNTAX      GEL2ESW26KSyslogDetailedInfoEntry
   MAX-ACCESS  not-accessible
   STATUS      current
   DESCRIPTION
           ""
   INDEX    { gel2esw26kSyslogDetailedInfoIndex  }
   ::= { gel2esw26kSyslogDetailedInfoTable 1 }

GEL2ESW26KSyslogDetailedInfoEntry ::= SEQUENCE {
   gel2esw26kSyslogDetailedInfoIndex       INTEGER,
   gel2esw26kSyslogDetailedInfoLevel       DisplayString,
   gel2esw26kSyslogDetailedInfoTime        DisplayString,
   gel2esw26kSyslogDetailedInfoMessage     DisplayString
}

gel2esw26kSyslogDetailedInfoIndex OBJECT-TYPE
   SYNTAX      INTEGER (1..1024)
   MAX-ACCESS  not-accessible
   STATUS      current
   DESCRIPTION
       " "
   ::= { gel2esw26kSyslogDetailedInfoEntry 1 }

gel2esw26kSyslogDetailedInfoLevel OBJECT-TYPE
   SYNTAX      DisplayString
   MAX-ACCESS  read-only
   STATUS      current
   DESCRIPTION
       " "
   ::= { gel2esw26kSyslogDetailedInfoEntry 2 }

gel2esw26kSyslogDetailedInfoTime OBJECT-TYPE
   SYNTAX      DisplayString(SIZE (0..20))
   MAX-ACCESS  read-only
   STATUS      current
   DESCRIPTION
       " "
   ::= { gel2esw26kSyslogDetailedInfoEntry 3 }

gel2esw26kSyslogDetailedInfoMessage OBJECT-TYPE
   SYNTAX      DisplayString
   MAX-ACCESS  read-only
   STATUS      current
   DESCRIPTION
       " "
   ::= { gel2esw26kSyslogDetailedInfoEntry 4 }


gel2esw26kSnmp                                                OBJECT IDENTIFIER ::= { gel2esw26kSystem 6 }

gel2esw26kSnmpConf                                            OBJECT IDENTIFIER ::= { gel2esw26kSnmp 1 }

gel2esw26kGetCommunity OBJECT-TYPE
   SYNTAX       DisplayString
   MAX-ACCESS   read-write
   STATUS       current
   DESCRIPTION
       "Get/Set the get-community of the SNMP."
   ::= { gel2esw26kSnmpConf 1 }

gel2esw26kSetCommunityMode OBJECT-TYPE
   SYNTAX       INTEGER(0|1)
   MAX-ACCESS   read-write
   STATUS       current
   DESCRIPTION
       "Get/Set the set-community mode of the SNMP.
        default : 1, 0: disable, 1: enable. "
   ::= { gel2esw26kSnmpConf 2 }

gel2esw26kSetCommunity OBJECT-TYPE
   SYNTAX       DisplayString
   MAX-ACCESS   read-write
   STATUS       current
   DESCRIPTION
       "Get/Set the set-community of the SNMP."
   ::= { gel2esw26kSnmpConf 3 }

gel2esw26kTrapHostConfTable OBJECT-TYPE
   SYNTAX      SEQUENCE OF GEL2ESW26KTrapHostConfEntry
   MAX-ACCESS  not-accessible
   STATUS      current
   DESCRIPTION
       "A list of trap host entry. The numbers of entries are given by the value of gel2esw26kTrapHostConfNumber."
   ::= { gel2esw26kSnmpConf 4 }

gel2esw26kTrapHostConfEntry OBJECT-TYPE
   SYNTAX      GEL2ESW26KTrapHostConfEntry
   MAX-ACCESS  not-accessible
   STATUS      current
   DESCRIPTION
       "This is the entry information for trap host."
   INDEX    { gel2esw26kTrapHostConfIndex  }
   ::= { gel2esw26kTrapHostConfTable 1 }

GEL2ESW26KTrapHostConfEntry ::= SEQUENCE {
    gel2esw26kTrapHostConfIndex             INTEGER,
    gel2esw26kTrapHostConfVersion           INTEGER,
    gel2esw26kTrapHostConfIPType            INTEGER,
    gel2esw26kTrapHostConfIP                DisplayString,
    gel2esw26kTrapHostConfPort              INTEGER,
    gel2esw26kTrapHostConfCommunity         DisplayString,
    gel2esw26kTrapHostConfSeverityLevel     INTEGER,
    gel2esw26kTrapHostConfSecurityLevel     INTEGER,
    gel2esw26kTrapHostConfAuthPtc           INTEGER,
    gel2esw26kTrapHostConfAuthPassword      DisplayString,
    gel2esw26kTrapHostConfPrivPtc           INTEGER,
    gel2esw26kTrapHostConfPrivPassword      DisplayString,
    gel2esw26kTrapHostConfCurrentMode       INTEGER
}

gel2esw26kTrapHostConfIndex OBJECT-TYPE
   SYNTAX      INTEGER (1..6)
   MAX-ACCESS  not-accessible
   STATUS      current
   DESCRIPTION
       " The index of the trap host entry. "
   ::= { gel2esw26kTrapHostConfEntry 1 }

gel2esw26kTrapHostConfVersion OBJECT-TYPE
   SYNTAX       INTEGER(2..3)
   MAX-ACCESS   read-write
   STATUS       current
   DESCRIPTION
       "The version of the Trap PDU. Version : 2(SNMPv2c), 3(SNMPv3)"
   ::= { gel2esw26kTrapHostConfEntry 2 }

gel2esw26kTrapHostConfIPType OBJECT-TYPE
   SYNTAX       INTEGER(4|6)
   MAX-ACCESS   read-write
   STATUS       current
   DESCRIPTION
       "Server IP Type. Default: 4,
        4 : IPv4,
        6 : IPv6."
   ::= { gel2esw26kTrapHostConfEntry 3 }

gel2esw26kTrapHostConfIP OBJECT-TYPE
   SYNTAX       DisplayString
   MAX-ACCESS   read-write
   STATUS       current
   DESCRIPTION
       "This is the IP of the trap host."
   ::= { gel2esw26kTrapHostConfEntry 4 }

gel2esw26kTrapHostConfPort OBJECT-TYPE
   SYNTAX       INTEGER(1..65535)
   MAX-ACCESS   read-write
   STATUS       current
   DESCRIPTION
       "This is the receiving-port number of the trap host.
        range : 1 - 65535."
   ::= { gel2esw26kTrapHostConfEntry 5 }

gel2esw26kTrapHostConfCommunity OBJECT-TYPE
   SYNTAX       DisplayString (SIZE (1..32))
   MAX-ACCESS   read-write
   STATUS       current
   DESCRIPTION
       "The community/security name for the trap PDU."
   ::= { gel2esw26kTrapHostConfEntry 6 }

gel2esw26kTrapHostConfSeverityLevel	OBJECT-TYPE
   SYNTAX       INTEGER(0..7)
   MAX-ACCESS   read-write
   STATUS       current
   DESCRIPTION
       "The Severity Level.
        0 : Emerg, 1 : Alert, 2 : Crit, 3 : Error, 4 : Warning, 5 : Notice, 6 : Info, 7 : Debug."
	::= { gel2esw26kTrapHostConfEntry 7 }

gel2esw26kTrapHostConfSecurityLevel	OBJECT-TYPE
   SYNTAX       INTEGER(1..3)
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gel2esw26kTrapHostConfEntry 8 }

gel2esw26kTrapHostConfAuthPtc	OBJECT-TYPE
   SYNTAX       INTEGER(1..2)
   MAX-ACCESS   read-write
   STATUS       current
   DESCRIPTION
       "Authentication Protocol, there are SHA and MD5 supported presently.
        1 : MD5, 2 : SHA."
	::= { gel2esw26kTrapHostConfEntry 9 }

gel2esw26kTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gel2esw26kTrapHostConfEntry 10 }

gel2esw26kTrapHostConfPrivPtc	OBJECT-TYPE
   SYNTAX       INTEGER(1)
   MAX-ACCESS   read-write
   STATUS       current
   DESCRIPTION
       "This is the Privacy Protocol, which is used in AuthPriv. Only supports DES.
        An empty string will be returned if the security level is not 3(AuthPriv).
        1 : DES."
	::= { gel2esw26kTrapHostConfEntry 11 }

gel2esw26kTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gel2esw26kTrapHostConfEntry 12 }

gel2esw26kTrapHostConfCurrentMode OBJECT-TYPE
   SYNTAX       INTEGER(0..2)
   MAX-ACCESS   read-write
   STATUS       current
   DESCRIPTION
       "0:Empty, 1:Active mode, 2:Edit mode, 3:Delete."
   ::= { gel2esw26kTrapHostConfEntry 13 }


----------------------------------------------------------------------------------------------------

gel2esw26kConfiguration                                         OBJECT IDENTIFIER ::= { gel2esw26kProductId 2 }

gel2esw26kPort                                                  OBJECT IDENTIFIER ::= { gel2esw26kConfiguration 1 }

gel2esw26kPortConfigurationTable OBJECT-TYPE
   SYNTAX      SEQUENCE OF GEL2ESW26KPortConfigurationEntry
   MAX-ACCESS  not-accessible
   STATUS      current
   DESCRIPTION
       " Show port configurations. "
   ::= { gel2esw26kPort 1 }

gel2esw26kPortConfigurationEntry OBJECT-TYPE
   SYNTAX      GEL2ESW26KPortConfigurationEntry
   MAX-ACCESS  not-accessible
   STATUS      current
   DESCRIPTION
       ""
   INDEX    { gel2esw26kPortConfPort  }
   ::= { gel2esw26kPortConfigurationTable 1 }

GEL2ESW26KPortConfigurationEntry ::= SEQUENCE {
   gel2esw26kPortConfPort                     INTEGER,
   gel2esw26kPortConfPortMedia                DisplayString,
   gel2esw26kPortConfLink                     DisplayString,
   gel2esw26kPortConfCurrentSpeed             DisplayString,
   gel2esw26kPortConfSpeed                    INTEGER,
   gel2esw26kPortConfCurrentFlowControlRx     INTEGER,
   gel2esw26kPortConfCurrentFlowControlTx     INTEGER,
   gel2esw26kPortConfFlowControl              INTEGER,
   gel2esw26kPortConfMaxFrameSize             INTEGER,
   gel2esw26kPortConfExcessiveCollisionMode   INTEGER,
   gel2esw26kPortConfPowerControl             INTEGER,
   gel2esw26kPortConfDescription              DisplayString
}

gel2esw26kPortConfPort OBJECT-TYPE
   SYNTAX      INTEGER (1..4095)
   MAX-ACCESS  not-accessible
   STATUS      current
   DESCRIPTION
       " port, range : 1 - port number. "
   ::= { gel2esw26kPortConfigurationEntry 1 }

gel2esw26kPortConfPortMedia OBJECT-TYPE
   SYNTAX      DisplayString(SIZE (1..4))
   MAX-ACCESS  read-only
   STATUS      current
   DESCRIPTION
       " Show port media. "
   ::= { gel2esw26kPortConfigurationEntry 2 }

gel2esw26kPortConfLink OBJECT-TYPE
   SYNTAX      DisplayString(SIZE (2..4))
   MAX-ACCESS  read-only
   STATUS      current
   DESCRIPTION
       " The current link state. "
   ::= { gel2esw26kPortConfigurationEntry 3 }

gel2esw26kPortConfCurrentSpeed OBJECT-TYPE
   SYNTAX      DisplayString(SIZE (6..12))
   MAX-ACCESS  read-only
   STATUS      current
   DESCRIPTION
       " The current link speed of the port. "
   ::= { gel2esw26kPortConfigurationEntry 4 }

gel2esw26kPortConfSpeed OBJECT-TYPE
   SYNTAX      INTEGER (0..11)
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X "
   ::= { gel2esw26kPortConfigurationEntry 5 }

gel2esw26kPortConfCurrentFlowControlRx OBJECT-TYPE
   SYNTAX      INTEGER (0|1)
   MAX-ACCESS  read-only
   STATUS      current
   DESCRIPTION
       "0: disable
        1: enable
        2: not support.  "
   ::= { gel2esw26kPortConfigurationEntry 6 }

gel2esw26kPortConfCurrentFlowControlTx OBJECT-TYPE
   SYNTAX      INTEGER (0|1)
   MAX-ACCESS  read-only
   STATUS      current
   DESCRIPTION
       "0: disable
        1: enable
        2: not support.  "
   ::= { gel2esw26kPortConfigurationEntry 7 }

gel2esw26kPortConfFlowControl OBJECT-TYPE
   SYNTAX      INTEGER (0|1)
   MAX-ACCESS  read-write
   STATUS      current
   DESCRIPTION
       "default: 0,
        0: disable
        1: enable
        2: not support. "
   ::= { gel2esw26kPortConfigurationEntry 8 }

gel2esw26kPortConfMaxFrameSize OBJECT-TYPE
   SYNTAX      INTEGER (1518..9600)
   MAX-ACCESS  read-write
   STATUS      current
   DESCRIPTION
       "default: 9600 , range : 1518 - 9600 "
   ::= { gel2esw26kPortConfigurationEntry 9 }

gel2esw26kPortConfExcessiveCollisionMode OBJECT-TYPE
   SYNTAX      INTEGER (0|1)
   MAX-ACCESS  read-write
   STATUS      current
   DESCRIPTION
       "default: 0,
        Excessive Collision Mode :
        0: Discard,
        1: Restart,
        2: not support.
       "
   ::= { gel2esw26kPortConfigurationEntry 10 }

gel2esw26kPortConfPowerControl OBJECT-TYPE
   SYNTAX      INTEGER (0..3)
   MAX-ACCESS  read-write
   STATUS      current
   DESCRIPTION
       "default: 0,
        PowerControl :
        0: disable,
        1: Actiphy,
        2: Dynamic (perfectReach),
        3: Enable,
        4: not support.
       "
   ::= { gel2esw26kPortConfigurationEntry 11 }

gel2esw26kPortConfDescription OBJECT-TYPE
   SYNTAX      DisplayString
   MAX-ACCESS  read-write
   STATUS      current
   DESCRIPTION
       " Interface specific description.
         Up to 47 characters describing this interface. "
   ::= { gel2esw26kPortConfigurationEntry 12 }


gel2esw26kPortTrafficStatisticsTable OBJECT-TYPE
   SYNTAX      SEQUENCE OF GEL2ESW26KPortTrafficStatisticsEntry
   MAX-ACCESS  not-accessible
   STATUS      current
   DESCRIPTION
       " "
   ::= { gel2esw26kPort 2 }

gel2esw26kPortTrafficStatisticsEntry OBJECT-TYPE
   SYNTAX      GEL2ESW26KPortTrafficStatisticsEntry
   MAX-ACCESS  not-accessible
   STATUS      current
   DESCRIPTION
       ""
   INDEX    { gel2esw26kPortTrafficStatisticsPort  }
   ::= { gel2esw26kPortTrafficStatisticsTable 1 }

GEL2ESW26KPortTrafficStatisticsEntry ::= SEQUENCE {
   gel2esw26kPortTrafficStatisticsPort          INTEGER,
   gel2esw26kPortTrafficStatisticsClear         INTEGER,
   gel2esw26kPortTrafficRxPackets               Counter64,
   gel2esw26kPortTrafficRxOctets                Counter64,
   gel2esw26kPortTrafficRxUnicast               Counter64,
   gel2esw26kPortTrafficRxMulticast             Counter64,
   gel2esw26kPortTrafficRxBroadcast             Counter64,
   gel2esw26kPortTrafficRxPause                 Counter64,
   gel2esw26kPortTrafficRx64Bytes               Counter64,
   gel2esw26kPortTrafficRx65to127Bytes          Counter64,
   gel2esw26kPortTrafficRx128to255Bytes         Counter64,
   gel2esw26kPortTrafficRx256to511Bytes         Counter64,
   gel2esw26kPortTrafficRx512to1023Bytes        Counter64,
   gel2esw26kPortTrafficRx1024to1526Bytes       Counter64,
   gel2esw26kPortTrafficRxExceecd1527Bytes      Counter64,
   gel2esw26kPortTrafficRxQ0                    Counter64,
   gel2esw26kPortTrafficRxQ1                    Counter64,
   gel2esw26kPortTrafficRxQ2                    Counter64,
   gel2esw26kPortTrafficRxQ3                    Counter64,
   gel2esw26kPortTrafficRxQ4                    Counter64,
   gel2esw26kPortTrafficRxQ5                    Counter64,
   gel2esw26kPortTrafficRxQ6                    Counter64,
   gel2esw26kPortTrafficRxQ7                    Counter64,
   gel2esw26kPortTrafficRxDrops                 Counter64,
   gel2esw26kPortTrafficRxCRCorAlignment        Counter64,
   gel2esw26kPortTrafficRxUndersize             Counter64,
   gel2esw26kPortTrafficRxOversize              Counter64,
   gel2esw26kPortTrafficRxFragments             Counter64,
   gel2esw26kPortTrafficRxJabber                Counter64,
   gel2esw26kPortTrafficRxFiltered              Counter64,
   gel2esw26kPortTrafficTxPackets               Counter64,
   gel2esw26kPortTrafficTxOctets                Counter64,
   gel2esw26kPortTrafficTxUnicast               Counter64,
   gel2esw26kPortTrafficTxMulticast             Counter64,
   gel2esw26kPortTrafficTxBroadcast             Counter64,
   gel2esw26kPortTrafficTxPause                 Counter64,
   gel2esw26kPortTrafficTx64Bytes               Counter64,
   gel2esw26kPortTrafficTx65to127Bytes          Counter64,
   gel2esw26kPortTrafficTx128to255Bytes         Counter64,
   gel2esw26kPortTrafficTx256to511Bytes         Counter64,
   gel2esw26kPortTrafficTx512to1023Bytes        Counter64,
   gel2esw26kPortTrafficTx1024to1526Bytes       Counter64,
   gel2esw26kPortTrafficTxExceecd1527Bytes      Counter64,
   gel2esw26kPortTrafficTxQ0                    Counter64,
   gel2esw26kPortTrafficTxQ1                    Counter64,
   gel2esw26kPortTrafficTxQ2                    Counter64,
   gel2esw26kPortTrafficTxQ3                    Counter64,
   gel2esw26kPortTrafficTxQ4                    Counter64,
   gel2esw26kPortTrafficTxQ5                    Counter64,
   gel2esw26kPortTrafficTxQ6                    Counter64,
   gel2esw26kPortTrafficTxQ7                    Counter64,
   gel2esw26kPortTrafficTxDrops                 Counter64,
   gel2esw26kPortTrafficTxLateOrExcColl         Counter64
}

gel2esw26kPortTrafficStatisticsPort OBJECT-TYPE
   SYNTAX      INTEGER (1..4095)
   MAX-ACCESS  not-accessible
   STATUS      current
   DESCRIPTION
       " "
   ::= { gel2esw26kPortTrafficStatisticsEntry 1 }

gel2esw26kPortTrafficStatisticsClear OBJECT-TYPE
   SYNTAX      INTEGER(0|1)
   MAX-ACCESS  read-write
   STATUS      current
   DESCRIPTION
       " "
   ::= { gel2esw26kPortTrafficStatisticsEntry 2 }

gel2esw26kPortTrafficRxPackets OBJECT-TYPE
   SYNTAX      Counter64
   MAX-ACCESS  read-only
   STATUS      current
   DESCRIPTION
       " "
   ::= { gel2esw26kPortTrafficStatisticsEntry 3 }

gel2esw26kPortTrafficRxOctets OBJECT-TYPE
   SYNTAX      Counter64
   MAX-ACCESS  read-only
   STATUS      current
   DESCRIPTION
       " "
   ::= { gel2esw26kPortTrafficStatisticsEntry 4 }

gel2esw26kPortTrafficRxUnicast OBJECT-TYPE
   SYNTAX      Counter64
   MAX-ACCESS  read-only
   STATUS      current
   DESCRIPTION
       " "
   ::= { gel2esw26kPortTrafficStatisticsEntry 5 }

gel2esw26kPortTrafficRxMulticast OBJECT-TYPE
   SYNTAX      Counter64
   MAX-ACCESS  read-only
   STATUS      current
   DESCRIPTION
       " "
   ::= { gel2esw26kPortTrafficStatisticsEntry 6 }

gel2esw26kPortTrafficRxBroadcast OBJECT-TYPE
   SYNTAX      Counter64
   MAX-ACCESS  read-only
   STATUS      current
   DESCRIPTION
       " "
   ::= { gel2esw26kPortTrafficStatisticsEntry 7 }

gel2esw26kPortTrafficRxPause OBJECT-TYPE
   SYNTAX      Counter64
   MAX-ACCESS  read-only
   STATUS      current
   DESCRIPTION
       " "
   ::= { gel2esw26kPortTrafficStatisticsEntry 8 }

gel2esw26kPortTrafficRx64Bytes OBJECT-TYPE
   SYNTAX      Counter64
   MAX-ACCESS  read-only
   STATUS      current
   DESCRIPTION
       " "
   ::= { gel2esw26kPortTrafficStatisticsEntry 9 }

gel2esw26kPortTrafficRx65to127Bytes OBJECT-TYPE
   SYNTAX      Counter64
   MAX-ACCESS  read-only
   STATUS      current
   DESCRIPTION
       " "
   ::= { gel2esw26kPortTrafficStatisticsEntry 10 }

gel2esw26kPortTrafficRx128to255Bytes OBJECT-TYPE
   SYNTAX      Counter64
   MAX-ACCESS  read-only
   STATUS      current
   DESCRIPTION
       " "
   ::= { gel2esw26kPortTrafficStatisticsEntry 11 }

gel2esw26kPortTrafficRx256to511Bytes OBJECT-TYPE
   SYNTAX      Counter64
   MAX-ACCESS  read-only
   STATUS      current
   DESCRIPTION
       " "
   ::= { gel2esw26kPortTrafficStatisticsEntry 12 }

gel2esw26kPortTrafficRx512to1023Bytes OBJECT-TYPE
   SYNTAX      Counter64
   MAX-ACCESS  read-only
   STATUS      current
   DESCRIPTION
       " "
   ::= { gel2esw26kPortTrafficStatisticsEntry 13 }

gel2esw26kPortTrafficRx1024to1526Bytes OBJECT-TYPE
   SYNTAX      Counter64
   MAX-ACCESS  read-only
   STATUS      current
   DESCRIPTION
       " "
   ::= { gel2esw26kPortTrafficStatisticsEntry 14 }

gel2esw26kPortTrafficRxExceecd1527Bytes OBJECT-TYPE
   SYNTAX      Counter64
   MAX-ACCESS  read-only
   STATUS      current
   DESCRIPTION
       " "
   ::= { gel2esw26kPortTrafficStatisticsEntry 15 }

gel2esw26kPortTrafficRxQ0 OBJECT-TYPE
   SYNTAX      Counter64
   MAX-ACCESS  read-only
   STATUS      current
   DESCRIPTION
       " "
   ::= { gel2esw26kPortTrafficStatisticsEntry 16 }

gel2esw26kPortTrafficRxQ1 OBJECT-TYPE
   SYNTAX      Counter64
   MAX-ACCESS  read-only
   STATUS      current
   DESCRIPTION
       " "
   ::= { gel2esw26kPortTrafficStatisticsEntry 17 }

gel2esw26kPortTrafficRxQ2 OBJECT-TYPE
   SYNTAX      Counter64
   MAX-ACCESS  read-only
   STATUS      current
   DESCRIPTION
       " "
   ::= { gel2esw26kPortTrafficStatisticsEntry 18 }

gel2esw26kPortTrafficRxQ3 OBJECT-TYPE
   SYNTAX      Counter64
   MAX-ACCESS  read-only
   STATUS      current
   DESCRIPTION
       " "
   ::= { gel2esw26kPortTrafficStatisticsEntry 19 }

gel2esw26kPortTrafficRxQ4 OBJECT-TYPE
   SYNTAX      Counter64
   MAX-ACCESS  read-only
   STATUS      current
   DESCRIPTION
       " "
   ::= { gel2esw26kPortTrafficStatisticsEntry 20 }

gel2esw26kPortTrafficRxQ5 OBJECT-TYPE
   SYNTAX      Counter64
   MAX-ACCESS  read-only
   STATUS      current
   DESCRIPTION
       " "
   ::= { gel2esw26kPortTrafficStatisticsEntry 21 }

gel2esw26kPortTrafficRxQ6 OBJECT-TYPE
   SYNTAX      Counter64
   MAX-ACCESS  read-only
   STATUS      current
   DESCRIPTION
       " "
   ::= { gel2esw26kPortTrafficStatisticsEntry 22 }

gel2esw26kPortTrafficRxQ7 OBJECT-TYPE
   SYNTAX      Counter64
   MAX-ACCESS  read-only
   STATUS      current
   DESCRIPTION
       " "
   ::= { gel2esw26kPortTrafficStatisticsEntry 23 }

gel2esw26kPortTrafficRxDrops OBJECT-TYPE
   SYNTAX      Counter64
   MAX-ACCESS  read-only
   STATUS      current
   DESCRIPTION
       " "
   ::= { gel2esw26kPortTrafficStatisticsEntry 24 }

gel2esw26kPortTrafficRxCRCorAlignment OBJECT-TYPE
   SYNTAX      Counter64
   MAX-ACCESS  read-only
   STATUS      current
   DESCRIPTION
       " "
   ::= { gel2esw26kPortTrafficStatisticsEntry 25 }

gel2esw26kPortTrafficRxUndersize OBJECT-TYPE
   SYNTAX      Counter64
   MAX-ACCESS  read-only
   STATUS      current
   DESCRIPTION
       " "
   ::= { gel2esw26kPortTrafficStatisticsEntry 26 }

gel2esw26kPortTrafficRxOversize OBJECT-TYPE
   SYNTAX      Counter64
   MAX-ACCESS  read-only
   STATUS      current
   DESCRIPTION
       " "
   ::= { gel2esw26kPortTrafficStatisticsEntry 27 }

gel2esw26kPortTrafficRxFragments OBJECT-TYPE
   SYNTAX      Counter64
   MAX-ACCESS  read-only
   STATUS      current
   DESCRIPTION
       " "
   ::= { gel2esw26kPortTrafficStatisticsEntry 28 }

gel2esw26kPortTrafficRxJabber OBJECT-TYPE
   SYNTAX      Counter64
   MAX-ACCESS  read-only
   STATUS      current
   DESCRIPTION
       " "
   ::= { gel2esw26kPortTrafficStatisticsEntry 29 }

gel2esw26kPortTrafficRxFiltered OBJECT-TYPE
   SYNTAX      Counter64
   MAX-ACCESS  read-only
   STATUS      current
   DESCRIPTION
       " "
   ::= { gel2esw26kPortTrafficStatisticsEntry 30 }

gel2esw26kPortTrafficTxPackets OBJECT-TYPE
   SYNTAX      Counter64
   MAX-ACCESS  read-only
   STATUS      current
   DESCRIPTION
       " "
   ::= { gel2esw26kPortTrafficStatisticsEntry 31 }

gel2esw26kPortTrafficTxOctets OBJECT-TYPE
   SYNTAX      Counter64
   MAX-ACCESS  read-only
   STATUS      current
   DESCRIPTION
       " "
   ::= { gel2esw26kPortTrafficStatisticsEntry 32 }

gel2esw26kPortTrafficTxUnicast OBJECT-TYPE
   SYNTAX      Counter64
   MAX-ACCESS  read-only
   STATUS      current
   DESCRIPTION
       " "
   ::= { gel2esw26kPortTrafficStatisticsEntry 33 }

gel2esw26kPortTrafficTxMulticast OBJECT-TYPE
   SYNTAX      Counter64
   MAX-ACCESS  read-only
   STATUS      current
   DESCRIPTION
       " "
   ::= { gel2esw26kPortTrafficStatisticsEntry 34 }

gel2esw26kPortTrafficTxBroadcast OBJECT-TYPE
   SYNTAX      Counter64
   MAX-ACCESS  read-only
   STATUS      current
   DESCRIPTION
       " "
   ::= { gel2esw26kPortTrafficStatisticsEntry 35 }

gel2esw26kPortTrafficTxPause OBJECT-TYPE
   SYNTAX      Counter64
   MAX-ACCESS  read-only
   STATUS      current
   DESCRIPTION
       " "
   ::= { gel2esw26kPortTrafficStatisticsEntry 36 }

gel2esw26kPortTrafficTx64Bytes OBJECT-TYPE
   SYNTAX      Counter64
   MAX-ACCESS  read-only
   STATUS      current
   DESCRIPTION
       " "
   ::= { gel2esw26kPortTrafficStatisticsEntry 37 }

gel2esw26kPortTrafficTx65to127Bytes OBJECT-TYPE
   SYNTAX      Counter64
   MAX-ACCESS  read-only
   STATUS      current
   DESCRIPTION
       " "
   ::= { gel2esw26kPortTrafficStatisticsEntry 38 }

gel2esw26kPortTrafficTx128to255Bytes OBJECT-TYPE
   SYNTAX      Counter64
   MAX-ACCESS  read-only
   STATUS      current
   DESCRIPTION
       " "
   ::= { gel2esw26kPortTrafficStatisticsEntry 39 }

gel2esw26kPortTrafficTx256to511Bytes OBJECT-TYPE
   SYNTAX      Counter64
   MAX-ACCESS  read-only
   STATUS      current
   DESCRIPTION
       " "
   ::= { gel2esw26kPortTrafficStatisticsEntry 40 }

gel2esw26kPortTrafficTx512to1023Bytes OBJECT-TYPE
   SYNTAX      Counter64
   MAX-ACCESS  read-only
   STATUS      current
   DESCRIPTION
       " "
   ::= { gel2esw26kPortTrafficStatisticsEntry 41 }

gel2esw26kPortTrafficTx1024to1526Bytes OBJECT-TYPE
   SYNTAX      Counter64
   MAX-ACCESS  read-only
   STATUS      current
   DESCRIPTION
       " "
   ::= { gel2esw26kPortTrafficStatisticsEntry 42 }

gel2esw26kPortTrafficTxExceecd1527Bytes OBJECT-TYPE
   SYNTAX      Counter64
   MAX-ACCESS  read-only
   STATUS      current
   DESCRIPTION
       " "
   ::= { gel2esw26kPortTrafficStatisticsEntry 43 }

gel2esw26kPortTrafficTxQ0 OBJECT-TYPE
   SYNTAX      Counter64
   MAX-ACCESS  read-only
   STATUS      current
   DESCRIPTION
       " "
   ::= { gel2esw26kPortTrafficStatisticsEntry 44 }

gel2esw26kPortTrafficTxQ1 OBJECT-TYPE
   SYNTAX      Counter64
   MAX-ACCESS  read-only
   STATUS      current
   DESCRIPTION
       " "
   ::= { gel2esw26kPortTrafficStatisticsEntry 45 }

gel2esw26kPortTrafficTxQ2 OBJECT-TYPE
   SYNTAX      Counter64
   MAX-ACCESS  read-only
   STATUS      current
   DESCRIPTION
       " "
   ::= { gel2esw26kPortTrafficStatisticsEntry 46 }

gel2esw26kPortTrafficTxQ3 OBJECT-TYPE
   SYNTAX      Counter64
   MAX-ACCESS  read-only
   STATUS      current
   DESCRIPTION
       " "
   ::= { gel2esw26kPortTrafficStatisticsEntry 47 }

gel2esw26kPortTrafficTxQ4 OBJECT-TYPE
   SYNTAX      Counter64
   MAX-ACCESS  read-only
   STATUS      current
   DESCRIPTION
       " "
   ::= { gel2esw26kPortTrafficStatisticsEntry 48 }

gel2esw26kPortTrafficTxQ5 OBJECT-TYPE
   SYNTAX      Counter64
   MAX-ACCESS  read-only
   STATUS      current
   DESCRIPTION
       " "
   ::= { gel2esw26kPortTrafficStatisticsEntry 49 }

gel2esw26kPortTrafficTxQ6 OBJECT-TYPE
   SYNTAX      Counter64
   MAX-ACCESS  read-only
   STATUS      current
   DESCRIPTION
       " "
   ::= { gel2esw26kPortTrafficStatisticsEntry 50 }


gel2esw26kPortTrafficTxQ7 OBJECT-TYPE
   SYNTAX      Counter64
   MAX-ACCESS  read-only
   STATUS      current
   DESCRIPTION
       " "
   ::= { gel2esw26kPortTrafficStatisticsEntry 51 }

gel2esw26kPortTrafficTxDrops OBJECT-TYPE
   SYNTAX      Counter64
   MAX-ACCESS  read-only
   STATUS      current
   DESCRIPTION
       " "
   ::= { gel2esw26kPortTrafficStatisticsEntry 52 }

gel2esw26kPortTrafficTxLateOrExcColl OBJECT-TYPE
   SYNTAX      Counter64
   MAX-ACCESS  read-only
   STATUS      current
   DESCRIPTION
       " "
   ::= { gel2esw26kPortTrafficStatisticsEntry 53 }


gel2esw26kPortQoSStatistics                                     OBJECT IDENTIFIER ::= { gel2esw26kPort 3 }

gel2esw26kPortQoSStatisticsClear OBJECT-TYPE
   SYNTAX      INTEGER(0|1)
   MAX-ACCESS  read-only
   STATUS      current
   DESCRIPTION
       "default: 0
       0: none
       1: clear "
   ::= { gel2esw26kPortQoSStatistics 1 }

gel2esw26kPortQoSStatisticsTable OBJECT-TYPE
   SYNTAX      SEQUENCE OF GEL2ESW26KPortQoSStatisticsEntry
   MAX-ACCESS  not-accessible
   STATUS      current
   DESCRIPTION
       " "
   ::= { gel2esw26kPortQoSStatistics 2 }

gel2esw26kPortQoSStatisticsEntry OBJECT-TYPE
   SYNTAX      GEL2ESW26KPortQoSStatisticsEntry
   MAX-ACCESS  not-accessible
   STATUS      current
   DESCRIPTION
       ""
   INDEX    { gel2esw26kPortQoSStatisticsPort  }
   ::= { gel2esw26kPortQoSStatisticsTable 1 }

GEL2ESW26KPortQoSStatisticsEntry ::= SEQUENCE {
   gel2esw26kPortQoSStatisticsPort      INTEGER,
   gel2esw26kPortQoSQ0Rx                Counter64,
   gel2esw26kPortQoSQ0Tx                Counter64,
   gel2esw26kPortQoSQ1Rx                Counter64,
   gel2esw26kPortQoSQ1Tx                Counter64,
   gel2esw26kPortQoSQ2Rx                Counter64,
   gel2esw26kPortQoSQ2Tx                Counter64,
   gel2esw26kPortQoSQ3Rx                Counter64,
   gel2esw26kPortQoSQ3Tx                Counter64,
   gel2esw26kPortQoSQ4Rx                Counter64,
   gel2esw26kPortQoSQ4Tx                Counter64,
   gel2esw26kPortQoSQ5Rx                Counter64,
   gel2esw26kPortQoSQ5Tx                Counter64,
   gel2esw26kPortQoSQ6Rx                Counter64,
   gel2esw26kPortQoSQ6Tx                Counter64,
   gel2esw26kPortQoSQ7Rx                Counter64,
   gel2esw26kPortQoSQ7Tx                Counter64
}

gel2esw26kPortQoSStatisticsPort OBJECT-TYPE
   SYNTAX      INTEGER (1..4095)
   MAX-ACCESS  not-accessible
   STATUS      current
   DESCRIPTION
       " "
   ::= { gel2esw26kPortQoSStatisticsEntry 1 }

gel2esw26kPortQoSQ0Rx OBJECT-TYPE
   SYNTAX      Counter64
   MAX-ACCESS  read-only
   STATUS      current
   DESCRIPTION
       " "
   ::= { gel2esw26kPortQoSStatisticsEntry 2 }

gel2esw26kPortQoSQ0Tx OBJECT-TYPE
   SYNTAX      Counter64
   MAX-ACCESS  read-only
   STATUS      current
   DESCRIPTION
       " "
   ::= { gel2esw26kPortQoSStatisticsEntry 3 }

gel2esw26kPortQoSQ1Rx OBJECT-TYPE
   SYNTAX      Counter64
   MAX-ACCESS  read-only
   STATUS      current
   DESCRIPTION
       " "
   ::= { gel2esw26kPortQoSStatisticsEntry 4 }

gel2esw26kPortQoSQ1Tx OBJECT-TYPE
   SYNTAX      Counter64
   MAX-ACCESS  read-only
   STATUS      current
   DESCRIPTION
       " "
   ::= { gel2esw26kPortQoSStatisticsEntry 5 }

gel2esw26kPortQoSQ2Rx OBJECT-TYPE
   SYNTAX      Counter64
   MAX-ACCESS  read-only
   STATUS      current
   DESCRIPTION
       " "
   ::= { gel2esw26kPortQoSStatisticsEntry 6 }

gel2esw26kPortQoSQ2Tx OBJECT-TYPE
   SYNTAX      Counter64
   MAX-ACCESS  read-only
   STATUS      current
   DESCRIPTION
       " "
   ::= { gel2esw26kPortQoSStatisticsEntry 7 }

gel2esw26kPortQoSQ3Rx OBJECT-TYPE
   SYNTAX      Counter64
   MAX-ACCESS  read-only
   STATUS      current
   DESCRIPTION
       " "
   ::= { gel2esw26kPortQoSStatisticsEntry 8 }

gel2esw26kPortQoSQ3Tx OBJECT-TYPE
   SYNTAX      Counter64
   MAX-ACCESS  read-only
   STATUS      current
   DESCRIPTION
       " "
   ::= { gel2esw26kPortQoSStatisticsEntry 9 }

gel2esw26kPortQoSQ4Rx OBJECT-TYPE
   SYNTAX      Counter64
   MAX-ACCESS  read-only
   STATUS      current
   DESCRIPTION
       " "
   ::= { gel2esw26kPortQoSStatisticsEntry 10 }

gel2esw26kPortQoSQ4Tx OBJECT-TYPE
   SYNTAX      Counter64
   MAX-ACCESS  read-only
   STATUS      current
   DESCRIPTION
       " "
   ::= { gel2esw26kPortQoSStatisticsEntry 11 }

gel2esw26kPortQoSQ5Rx OBJECT-TYPE
   SYNTAX      Counter64
   MAX-ACCESS  read-only
   STATUS      current
   DESCRIPTION
       " "
   ::= { gel2esw26kPortQoSStatisticsEntry 12 }

gel2esw26kPortQoSQ5Tx OBJECT-TYPE
   SYNTAX      Counter64
   MAX-ACCESS  read-only
   STATUS      current
   DESCRIPTION
       " "
   ::= { gel2esw26kPortQoSStatisticsEntry 13 }

gel2esw26kPortQoSQ6Rx OBJECT-TYPE
   SYNTAX      Counter64
   MAX-ACCESS  read-only
   STATUS      current
   DESCRIPTION
       " "
   ::= { gel2esw26kPortQoSStatisticsEntry 14 }

gel2esw26kPortQoSQ6Tx OBJECT-TYPE
   SYNTAX      Counter64
   MAX-ACCESS  read-only
   STATUS      current
   DESCRIPTION
       " "
   ::= { gel2esw26kPortQoSStatisticsEntry 15 }

gel2esw26kPortQoSQ7Rx OBJECT-TYPE
   SYNTAX      Counter64
   MAX-ACCESS  read-only
   STATUS      current
   DESCRIPTION
       " "
   ::= { gel2esw26kPortQoSStatisticsEntry 16 }

gel2esw26kPortQoSQ7Tx OBJECT-TYPE
   SYNTAX      Counter64
   MAX-ACCESS  read-only
   STATUS      current
   DESCRIPTION
       " "
   ::= { gel2esw26kPortQoSStatisticsEntry 17 }

gel2esw26kSFPInfoTable OBJECT-TYPE
   SYNTAX      SEQUENCE OF GEL2ESW26KSFPInfoEntry
   MAX-ACCESS  not-accessible
   STATUS      current
   DESCRIPTION
       " "
   ::= { gel2esw26kPort 4 }

gel2esw26kSFPInfoEntry OBJECT-TYPE
   SYNTAX      GEL2ESW26KSFPInfoEntry
   MAX-ACCESS  not-accessible
   STATUS      current
   DESCRIPTION
       ""
   INDEX    { gel2esw26kSFPInfoIndex }
   ::= { gel2esw26kSFPInfoTable 1 }

GEL2ESW26KSFPInfoEntry ::= SEQUENCE {
   gel2esw26kSFPInfoIndex               INTEGER,
   gel2esw26kSFPInfoPort                DisplayString,
   gel2esw26kSFPConnectorType           DisplayString,
   gel2esw26kSFPFiberType               DisplayString,
   gel2esw26kSFPTxCentralWavelength     DisplayString,
   gel2esw26kSFPBaudRate                DisplayString,
   gel2esw26kSFPVendorOUI               DisplayString,
   gel2esw26kSFPVendorName              DisplayString,
   gel2esw26kSFPVendorPN                DisplayString,
   gel2esw26kSFPVendorRev               DisplayString,
   gel2esw26kSFPVendorSN                DisplayString,
   gel2esw26kSFPDateCode                DisplayString,
   gel2esw26kSFPTemperature             DisplayString,
   gel2esw26kSFPVcc                     DisplayString,
   gel2esw26kSFPMon1Bias                DisplayString,
   gel2esw26kSFPMon2TxPWR               DisplayString,
   gel2esw26kSFPMon3RxPWR               DisplayString
}

gel2esw26kSFPInfoIndex OBJECT-TYPE
   SYNTAX      INTEGER (1..4095)
   MAX-ACCESS  not-accessible
   STATUS      current
   DESCRIPTION
       " "
   ::= { gel2esw26kSFPInfoEntry 1 }

gel2esw26kSFPInfoPort OBJECT-TYPE
   SYNTAX      DisplayString
   MAX-ACCESS  read-only
   STATUS      current
   DESCRIPTION
       " "
   ::= { gel2esw26kSFPInfoEntry 2 }

gel2esw26kSFPConnectorType OBJECT-TYPE
   SYNTAX      DisplayString
   MAX-ACCESS  read-only
   STATUS      current
   DESCRIPTION
       " "
   ::= { gel2esw26kSFPInfoEntry 3 }

gel2esw26kSFPFiberType OBJECT-TYPE
   SYNTAX      DisplayString
   MAX-ACCESS  read-only
   STATUS      current
   DESCRIPTION
       " "
   ::= { gel2esw26kSFPInfoEntry 4 }

gel2esw26kSFPTxCentralWavelength OBJECT-TYPE
   SYNTAX      DisplayString
   MAX-ACCESS  read-only
   STATUS      current
   DESCRIPTION
       " "
   ::= { gel2esw26kSFPInfoEntry 5 }

gel2esw26kSFPBaudRate OBJECT-TYPE
   SYNTAX      DisplayString
   MAX-ACCESS  read-only
   STATUS      current
   DESCRIPTION
       " "
   ::= { gel2esw26kSFPInfoEntry 6 }

gel2esw26kSFPVendorOUI OBJECT-TYPE
   SYNTAX      DisplayString
   MAX-ACCESS  read-only
   STATUS      current
   DESCRIPTION
       " "
   ::= { gel2esw26kSFPInfoEntry 7 }

gel2esw26kSFPVendorName OBJECT-TYPE
   SYNTAX      DisplayString
   MAX-ACCESS  read-only
   STATUS      current
   DESCRIPTION
       " "
   ::= { gel2esw26kSFPInfoEntry 8 }

gel2esw26kSFPVendorPN OBJECT-TYPE
   SYNTAX      DisplayString
   MAX-ACCESS  read-only
   STATUS      current
   DESCRIPTION
       " "
   ::= { gel2esw26kSFPInfoEntry 9 }

gel2esw26kSFPVendorRev OBJECT-TYPE
   SYNTAX      DisplayString
   MAX-ACCESS  read-only
   STATUS      current
   DESCRIPTION
       " "
   ::= { gel2esw26kSFPInfoEntry 10 }

gel2esw26kSFPVendorSN OBJECT-TYPE
   SYNTAX      DisplayString
   MAX-ACCESS  read-only
   STATUS      current
   DESCRIPTION
       " "
   ::= { gel2esw26kSFPInfoEntry 11 }

gel2esw26kSFPDateCode OBJECT-TYPE
   SYNTAX      DisplayString
   MAX-ACCESS  read-only
   STATUS      current
   DESCRIPTION
       " "
   ::= { gel2esw26kSFPInfoEntry 12 }

gel2esw26kSFPTemperature OBJECT-TYPE
   SYNTAX      DisplayString
   MAX-ACCESS  read-only
   STATUS      current
   DESCRIPTION
       " "
   ::= { gel2esw26kSFPInfoEntry 13 }

gel2esw26kSFPVcc OBJECT-TYPE
   SYNTAX      DisplayString
   MAX-ACCESS  read-only
   STATUS      current
   DESCRIPTION
       " "
   ::= { gel2esw26kSFPInfoEntry 14 }

gel2esw26kSFPMon1Bias OBJECT-TYPE
   SYNTAX      DisplayString
   MAX-ACCESS  read-only
   STATUS      current
   DESCRIPTION
       " "
   ::= { gel2esw26kSFPInfoEntry 15 }

gel2esw26kSFPMon2TxPWR OBJECT-TYPE
   SYNTAX      DisplayString
   MAX-ACCESS  read-only
   STATUS      current
   DESCRIPTION
       " "
   ::= { gel2esw26kSFPInfoEntry 16 }

gel2esw26kSFPMon3RxPWR OBJECT-TYPE
   SYNTAX      DisplayString
   MAX-ACCESS  read-only
   STATUS      current
   DESCRIPTION
       " "
   ::= { gel2esw26kSFPInfoEntry 17 }


gel2esw26kPortEEETable OBJECT-TYPE
   SYNTAX      SEQUENCE OF GEL2ESW26KPortEEEEntry
   MAX-ACCESS  not-accessible
   STATUS      current
   DESCRIPTION
      " "
   ::= { gel2esw26kPort 5 }

gel2esw26kPortEEEEntry OBJECT-TYPE
   SYNTAX      GEL2ESW26KPortEEEEntry
   MAX-ACCESS  not-accessible
   STATUS      current
   DESCRIPTION
       ""
   INDEX    { gel2esw26kPortEEEPort }
   ::= { gel2esw26kPortEEETable 1 }

GEL2ESW26KPortEEEEntry ::= SEQUENCE {
   gel2esw26kPortEEEPort		        INTEGER,
   gel2esw26kPortEEEMode		        INTEGER,
   gel2esw26kPortEEEUrgentQueue1		INTEGER,
   gel2esw26kPortEEEUrgentQueue2		INTEGER,
   gel2esw26kPortEEEUrgentQueue3		INTEGER,
   gel2esw26kPortEEEUrgentQueue4		INTEGER,
   gel2esw26kPortEEEUrgentQueue5		INTEGER,
   gel2esw26kPortEEEUrgentQueue6		INTEGER,
   gel2esw26kPortEEEUrgentQueue7		INTEGER,
   gel2esw26kPortEEEUrgentQueue8		INTEGER
}

gel2esw26kPortEEEPort OBJECT-TYPE
   SYNTAX      INTEGER (1..4095)
   MAX-ACCESS  not-accessible
   STATUS      current
   DESCRIPTION
       " "
   ::= { gel2esw26kPortEEEEntry 1 }

gel2esw26kPortEEEMode OBJECT-TYPE
   SYNTAX      INTEGER(0|1)
   MAX-ACCESS  read-write
   STATUS      current
   DESCRIPTION
       "default: 0
       0:disable
       1:enable "
   ::= { gel2esw26kPortEEEEntry 2 }

gel2esw26kPortEEEUrgentQueue1 OBJECT-TYPE
   SYNTAX      INTEGER(0|1)
   MAX-ACCESS  read-write
   STATUS      current
   DESCRIPTION
       "default: 0
       0:disable
       1:enable "
   ::= { gel2esw26kPortEEEEntry 3 }

gel2esw26kPortEEEUrgentQueue2 OBJECT-TYPE
   SYNTAX      INTEGER(0|1)
   MAX-ACCESS  read-write
   STATUS      current
   DESCRIPTION
       "default: 0
       0:disable
       1:enable "
   ::= { gel2esw26kPortEEEEntry 4 }

gel2esw26kPortEEEUrgentQueue3 OBJECT-TYPE
   SYNTAX      INTEGER(0|1)
   MAX-ACCESS  read-write
   STATUS      current
   DESCRIPTION
       "default: 0
       0:disable
       1:enable "
   ::= { gel2esw26kPortEEEEntry 5 }

gel2esw26kPortEEEUrgentQueue4 OBJECT-TYPE
   SYNTAX      INTEGER(0|1)
   MAX-ACCESS  read-write
   STATUS      current
   DESCRIPTION
       "default: 0
       0:disable
       1:enable "
   ::= { gel2esw26kPortEEEEntry 6 }

gel2esw26kPortEEEUrgentQueue5 OBJECT-TYPE
   SYNTAX      INTEGER(0|1)
   MAX-ACCESS  read-write
   STATUS      current
   DESCRIPTION
       "default: 0
       0:disable
       1:enable "
   ::= { gel2esw26kPortEEEEntry 7 }

gel2esw26kPortEEEUrgentQueue6 OBJECT-TYPE
   SYNTAX      INTEGER(0|1)
   MAX-ACCESS  read-write
   STATUS      current
   DESCRIPTION
       "default: 0
       0:disable
       1:enable "
   ::= { gel2esw26kPortEEEEntry 8 }

gel2esw26kPortEEEUrgentQueue7 OBJECT-TYPE
   SYNTAX      INTEGER(0|1)
   MAX-ACCESS  read-write
   STATUS      current
   DESCRIPTION
       "default: 0
       0:disable
       1:enable "
   ::= { gel2esw26kPortEEEEntry 9 }

gel2esw26kPortEEEUrgentQueue8 OBJECT-TYPE
   SYNTAX      INTEGER(0|1)
   MAX-ACCESS  read-write
   STATUS      current
   DESCRIPTION
       "default: 0
       0:disable
       1:enable "
   ::= { gel2esw26kPortEEEEntry 10 }


gel2esw26kVoiceVLAN                                             OBJECT IDENTIFIER ::= { gel2esw26kConfiguration 2 }

gel2esw26kVoiceVLANConf                                         OBJECT IDENTIFIER ::= { gel2esw26kVoiceVLAN 1 }

gel2esw26kVoiceVLANMode OBJECT-TYPE
   SYNTAX      INTEGER (0|1)
   MAX-ACCESS  read-write
   STATUS      current
   DESCRIPTION
       " Voice VLAN mode operation.
       default: 0,
       0: disable
       1: enable"
   ::= { gel2esw26kVoiceVLANConf 1 }

gel2esw26kVoiceVLANVLANId OBJECT-TYPE
   SYNTAX      INTEGER (1..4094)
   MAX-ACCESS  read-write
   STATUS      current
   DESCRIPTION
       "Voice VLAN ID.
        default: 1000,
        range : 1-4094. "
   ::= { gel2esw26kVoiceVLANConf 2 }

gel2esw26kVoiceVLANAgingTime OBJECT-TYPE
   SYNTAX      INTEGER (10..1000000)
   MAX-ACCESS  read-write
   STATUS      current
   DESCRIPTION
       " Voice VLAN secure learning aging time.
         default: 86400,
         range : 10 - 10000000. "
   ::= { gel2esw26kVoiceVLANConf 3 }

gel2esw26kVoiceVLANTrafficClass OBJECT-TYPE
   SYNTAX      INTEGER (0..7)
   MAX-ACCESS  read-write
   STATUS      current
   DESCRIPTION
       " Voice VLAN traffic class, all traffic on the Voice VLAN
         will apply this class, available value is from 0(Low)
         to 7(High).
         default: 7. "
   ::= { gel2esw26kVoiceVLANConf 4 }


gel2esw26kVoiceVLANPortTable OBJECT-TYPE
   SYNTAX      SEQUENCE OF GEL2ESW26KVoiceVLANPortEntry
   MAX-ACCESS  not-accessible
   STATUS      current
   DESCRIPTION
       " Show Voice Vlan configuration. "
   ::= { gel2esw26kVoiceVLANConf 5 }

gel2esw26kVoiceVLANPortEntry OBJECT-TYPE
   SYNTAX      GEL2ESW26KVoiceVLANPortEntry
   MAX-ACCESS  not-accessible
   STATUS      current
   DESCRIPTION
       ""
   INDEX    { gel2esw26kVoiceVLANPort  }
   ::= { gel2esw26kVoiceVLANPortTable 1 }

GEL2ESW26KVoiceVLANPortEntry ::= SEQUENCE {
   gel2esw26kVoiceVLANPort                    INTEGER,
   gel2esw26kVoiceVLANPortMode                INTEGER,
   gel2esw26kVoiceVLANPortSecurity            INTEGER,
   gel2esw26kVoiceVLANPortDiscoveryProtocol   INTEGER
}

gel2esw26kVoiceVLANPort OBJECT-TYPE
   SYNTAX      INTEGER (1..4095)
   MAX-ACCESS  not-accessible
   STATUS      current
   DESCRIPTION
       " port, range : 1 - port number. "
   ::= { gel2esw26kVoiceVLANPortEntry 1 }

gel2esw26kVoiceVLANPortMode OBJECT-TYPE
   SYNTAX      INTEGER (0..2)
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { gel2esw26kVoiceVLANPortEntry 2 }

gel2esw26kVoiceVLANPortSecurity OBJECT-TYPE
   SYNTAX      INTEGER (0|1)
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { gel2esw26kVoiceVLANPortEntry 3 }

gel2esw26kVoiceVLANPortDiscoveryProtocol OBJECT-TYPE
   SYNTAX      INTEGER (0..2)
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { gel2esw26kVoiceVLANPortEntry 4 }


gel2esw26kVoiceVLANOUI                                          OBJECT IDENTIFIER ::= { gel2esw26kVoiceVLAN 2 }

gel2esw26kVoiceVLANOUICreate OBJECT-TYPE
   SYNTAX       INTEGER(0|1)
   MAX-ACCESS   read-write
   STATUS       current
   DESCRIPTION
       "default: 0
        0 : None  (read only)
        1 : Create an OUI entry"
   ::= { gel2esw26kVoiceVLANOUI 1 }

gel2esw26kVoiceVLANOUITable OBJECT-TYPE
   SYNTAX      SEQUENCE OF GEL2ESW26KVoiceVLANOUIEntry
   MAX-ACCESS  not-accessible
   STATUS      current
   DESCRIPTION
       " Create Voice VLAN OUI entry. Modify OUI table will
         restart auto detect OUI process. "
   ::= { gel2esw26kVoiceVLANOUI 2 }

gel2esw26kVoiceVLANOUIEntry OBJECT-TYPE
   SYNTAX      GEL2ESW26KVoiceVLANOUIEntry
   MAX-ACCESS  not-accessible
   STATUS      current
   DESCRIPTION
       ""
   INDEX    { gel2esw26kVoiceVLANOUIIndex  }
   ::= { gel2esw26kVoiceVLANOUITable 1 }

GEL2ESW26KVoiceVLANOUIEntry ::= SEQUENCE {
   gel2esw26kVoiceVLANOUIIndex         INTEGER,
   gel2esw26kVoiceVLANTelephonyOUI     OCTET STRING,
   gel2esw26kVoiceVLANDescription      DisplayString,
   gel2esw26kVoiceVLANOUIRowStatus     INTEGER
}

gel2esw26kVoiceVLANOUIIndex OBJECT-TYPE
   SYNTAX      INTEGER (1..16)
   MAX-ACCESS  not-accessible
   STATUS      current
   DESCRIPTION
       " "
   ::= { gel2esw26kVoiceVLANOUIEntry 1 }

gel2esw26kVoiceVLANTelephonyOUI OBJECT-TYPE
   SYNTAX      OCTET STRING (SIZE (1..32))
   MAX-ACCESS  read-write
   STATUS      current
   DESCRIPTION
       "OUI address, format : 0a 1b 2c "
   ::= { gel2esw26kVoiceVLANOUIEntry 2 }

gel2esw26kVoiceVLANDescription OBJECT-TYPE
   SYNTAX      DisplayString (SIZE (1..32))
   MAX-ACCESS  read-write
   STATUS      current
   DESCRIPTION
       " Up to 32 characters describing OUI address. "
   ::= { gel2esw26kVoiceVLANOUIEntry 3 }

gel2esw26kVoiceVLANOUIRowStatus OBJECT-TYPE
   SYNTAX      INTEGER (1..5)
   MAX-ACCESS  read-write
   STATUS      current
   DESCRIPTION
       "1: active
        2: notInservice
        4: destroy
        5: undo"
   ::= { gel2esw26kVoiceVLANOUIEntry 4 }

gel2esw26kGARP                                                   OBJECT IDENTIFIER ::= { gel2esw26kConfiguration 3 }

gel2esw26kGARPConfTable OBJECT-TYPE
   SYNTAX      SEQUENCE OF GEL2ESW26KGARPConfEntry
   MAX-ACCESS  not-accessible
   STATUS      current
   DESCRIPTION
       " "
   ::= { gel2esw26kGARP 1 }

gel2esw26kGARPConfEntry OBJECT-TYPE
   SYNTAX      GEL2ESW26KGARPConfEntry
   MAX-ACCESS  not-accessible
   STATUS      current
   DESCRIPTION
       ""
   INDEX    { gel2esw26kGARPConfPort  }
   ::= { gel2esw26kGARPConfTable 1 }

GEL2ESW26KGARPConfEntry ::= SEQUENCE {
   gel2esw26kGARPConfPort           INTEGER,
   gel2esw26kGARPJoinTimer          INTEGER,
   gel2esw26kGARPLeaveTimer         INTEGER,
   gel2esw26kGARPLeaveAllTimer      INTEGER,
   gel2esw26kGARPApplicantion       INTEGER,
   gel2esw26kGARPAttributeType      INTEGER,
   gel2esw26kGARPApplicant          INTEGER
}

gel2esw26kGARPConfPort OBJECT-TYPE
   SYNTAX      INTEGER (1..4095)
   MAX-ACCESS  not-accessible
   STATUS      current
   DESCRIPTION
       " "
   ::= { gel2esw26kGARPConfEntry 1 }

gel2esw26kGARPJoinTimer OBJECT-TYPE
   SYNTAX      INTEGER (200..1000)
   MAX-ACCESS  read-write
   STATUS      current
   DESCRIPTION
       "default: 200, range : 200 - 1000 "
   ::= { gel2esw26kGARPConfEntry 2 }

gel2esw26kGARPLeaveTimer OBJECT-TYPE
   SYNTAX      INTEGER (600..3000)
   MAX-ACCESS  read-write
   STATUS      current
   DESCRIPTION
       "default: 600 , range : 600 - 3000"
   ::= { gel2esw26kGARPConfEntry 3 }

gel2esw26kGARPLeaveAllTimer OBJECT-TYPE
   SYNTAX      INTEGER (10000..50000)
   MAX-ACCESS  read-write
   STATUS      current
   DESCRIPTION
       "default: 10000, range : 10000 - 50000 "
   ::= { gel2esw26kGARPConfEntry 4 }

gel2esw26kGARPApplicantion OBJECT-TYPE
   SYNTAX      INTEGER(1)
   MAX-ACCESS  read-write
   STATUS      current
   DESCRIPTION
       "default: 1
       1: GVRP"
   ::= { gel2esw26kGARPConfEntry 5 }

gel2esw26kGARPAttributeType OBJECT-TYPE
   SYNTAX      INTEGER(1)
   MAX-ACCESS  read-write
   STATUS      current
   DESCRIPTION
       "default: 1
       1: VLAN"
   ::= { gel2esw26kGARPConfEntry 6 }

gel2esw26kGARPApplicant OBJECT-TYPE
   SYNTAX      INTEGER(0|1)
   MAX-ACCESS  read-write
   STATUS      current
   DESCRIPTION
       "default: 0
       0: normal-participant
       1: non-participant"
   ::= { gel2esw26kGARPConfEntry 7 }

gel2esw26kGARPStatisticsTable OBJECT-TYPE
   SYNTAX      SEQUENCE OF GEL2ESW26KGARPStatisticsEntry
   MAX-ACCESS  not-accessible
   STATUS      current
   DESCRIPTION
       " Show the basic GARP port statistics. "
   ::= { gel2esw26kGARP 2 }

gel2esw26kGARPStatisticsEntry OBJECT-TYPE
   SYNTAX      GEL2ESW26KGARPStatisticsEntry
   MAX-ACCESS  not-accessible
   STATUS      current
   DESCRIPTION
       ""
   INDEX    { gel2esw26kGARPStatisticsPort  }
   ::= { gel2esw26kGARPStatisticsTable 1 }

GEL2ESW26KGARPStatisticsEntry ::= SEQUENCE {
   gel2esw26kGARPStatisticsPort             INTEGER,
   gel2esw26kGARPStatisticsPeerMAC          DisplayString,
   gel2esw26kGARPStatisticsFailedCount      Counter32
}

gel2esw26kGARPStatisticsPort OBJECT-TYPE
   SYNTAX      INTEGER (1..4095)
   MAX-ACCESS  not-accessible
   STATUS      current
   DESCRIPTION
       " port, range : 1 - port number. "
   ::= { gel2esw26kGARPStatisticsEntry 1 }

gel2esw26kGARPStatisticsPeerMAC OBJECT-TYPE
   SYNTAX      DisplayString
   MAX-ACCESS  read-only
   STATUS      current
   DESCRIPTION
       " Peer MAC is MAC address of the neighbour Switch from with GARP frame is received.  "
   ::= { gel2esw26kGARPStatisticsEntry 2 }

gel2esw26kGARPStatisticsFailedCount OBJECT-TYPE
   SYNTAX      Counter32
   MAX-ACCESS  read-only
   STATUS      current
   DESCRIPTION
       " explain Failed count here. "
   ::= { gel2esw26kGARPStatisticsEntry 3 }

gel2esw26kGVRP                                                   OBJECT IDENTIFIER ::= { gel2esw26kConfiguration 4 }

gel2esw26kGVRPConf                                                   OBJECT IDENTIFIER ::= { gel2esw26kGVRP 1 }

gel2esw26kGVRPMode OBJECT-TYPE
   SYNTAX      INTEGER(0|1)
   MAX-ACCESS  read-write
   STATUS      current
   DESCRIPTION
       "default: 0,
        0: disable,
        1: enable. "
   ::= { gel2esw26kGVRPConf 1 }

gel2esw26kGVRPConfTable OBJECT-TYPE
   SYNTAX      SEQUENCE OF GEL2ESW26KGVRPConfEntry
   MAX-ACCESS  not-accessible
   STATUS      current
   DESCRIPTION
       " "
   ::= { gel2esw26kGVRPConf 2 }

gel2esw26kGVRPConfEntry OBJECT-TYPE
   SYNTAX      GEL2ESW26KGVRPConfEntry
   MAX-ACCESS  not-accessible
   STATUS      current
   DESCRIPTION
       ""
   INDEX    { gel2esw26kGVRPConfPort  }
   ::= { gel2esw26kGVRPConfTable 1 }

GEL2ESW26KGVRPConfEntry ::= SEQUENCE {
   gel2esw26kGVRPConfPort           INTEGER,
   gel2esw26kGVRPConfPortMode       INTEGER,
   gel2esw26kGVRPConfPortRRole      INTEGER
}

gel2esw26kGVRPConfPort OBJECT-TYPE
   SYNTAX      INTEGER (1..4095)
   MAX-ACCESS  not-accessible
   STATUS      current
   DESCRIPTION
       " "
   ::= { gel2esw26kGVRPConfEntry 1 }

gel2esw26kGVRPConfPortMode OBJECT-TYPE
   SYNTAX      INTEGER(0|1)
   MAX-ACCESS  read-write
   STATUS      current
   DESCRIPTION
       "default: 0
       1: enable
       0: disable"
   ::= { gel2esw26kGVRPConfEntry 2 }

gel2esw26kGVRPConfPortRRole OBJECT-TYPE
   SYNTAX      INTEGER(0|1)
   MAX-ACCESS  read-write
   STATUS      current
   DESCRIPTION
       "default: 0
       1: enable
       0: disable"
   ::= { gel2esw26kGVRPConfEntry 3 }

gel2esw26kGVRPStatisticsTable OBJECT-TYPE
   SYNTAX      SEQUENCE OF GEL2ESW26KGVRPStatisticsEntry
   MAX-ACCESS  not-accessible
   STATUS      current
   DESCRIPTION
       " "
   ::= { gel2esw26kGVRP 2 }

gel2esw26kGVRPStatisticsEntry OBJECT-TYPE
   SYNTAX      GEL2ESW26KGVRPStatisticsEntry
   MAX-ACCESS  not-accessible
   STATUS      current
   DESCRIPTION
       ""
   INDEX    { gel2esw26kGVRPStatisticsPort  }
   ::= { gel2esw26kGVRPStatisticsTable 1 }

GEL2ESW26KGVRPStatisticsEntry ::= SEQUENCE {
   gel2esw26kGVRPStatisticsPort         INTEGER,
   gel2esw26kGVRPStatisticsJoinTxCnt    Counter32,
   gel2esw26kGVRPStatisticsLeaveTxCnt   Counter32
}

gel2esw26kGVRPStatisticsPort OBJECT-TYPE
   SYNTAX      INTEGER (1..4095)
   MAX-ACCESS  not-accessible
   STATUS      current
   DESCRIPTION
       " "
   ::= { gel2esw26kGVRPStatisticsEntry 1 }

gel2esw26kGVRPStatisticsJoinTxCnt OBJECT-TYPE
   SYNTAX      Counter32
   MAX-ACCESS  read-only
   STATUS      current
   DESCRIPTION
       ""
   ::= { gel2esw26kGVRPStatisticsEntry 2 }

gel2esw26kGVRPStatisticsLeaveTxCnt OBJECT-TYPE
   SYNTAX      Counter32
   MAX-ACCESS  read-only
   STATUS      current
   DESCRIPTION
       ""
   ::= { gel2esw26kGVRPStatisticsEntry 3 }


gel2esw26kMirroring                                             OBJECT IDENTIFIER ::= { gel2esw26kConfiguration 6 }

gel2esw26kPortToMirrorOn OBJECT-TYPE
   SYNTAX      INTEGER(0..10)
   MAX-ACCESS  read-write
   STATUS      current
   DESCRIPTION
       "default: 0
        0: disable,
        range : 1 - port number. "
   ::= { gel2esw26kMirroring 1 }

gel2esw26kMirrorTable OBJECT-TYPE
   SYNTAX      SEQUENCE OF GEL2ESW26KMirrorEntry
   MAX-ACCESS  not-accessible
   STATUS      current
   DESCRIPTION
       " "
   ::= { gel2esw26kMirroring 2 }

gel2esw26kMirrorEntry OBJECT-TYPE
   SYNTAX      GEL2ESW26KMirrorEntry
   MAX-ACCESS  not-accessible
   STATUS      current
   DESCRIPTION
       ""
   INDEX    { gel2esw26kMirrorPort  }
   ::= { gel2esw26kMirrorTable 1 }

GEL2ESW26KMirrorEntry ::= SEQUENCE {
   gel2esw26kMirrorPort		INTEGER,
   gel2esw26kMirrorMode		INTEGER
}

gel2esw26kMirrorPort OBJECT-TYPE
   SYNTAX      INTEGER (1..4095)
   MAX-ACCESS  not-accessible
   STATUS      current
   DESCRIPTION
       " "
   ::= { gel2esw26kMirrorEntry 1 }

gel2esw26kMirrorMode OBJECT-TYPE
   SYNTAX      INTEGER(0..3)
   MAX-ACCESS  read-write
   STATUS      current
   DESCRIPTION
       "default: 0
       0: disable
       1: enable
       2: rx only
       3: tx only
       Setting Tx mirroring for analyzer port has no effect. Tx mirroring ignored"
   ::= { gel2esw26kMirrorEntry 2 }

gel2esw26kTrapEventSeverity                                             OBJECT IDENTIFIER ::= { gel2esw26kConfiguration 7 }

gel2esw26kTrapEventSeverityACL OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 1 }

gel2esw26kTrapEventSeverityACLLog OBJECT-TYPE
   SYNTAX      INTEGER (0..7)
   MAX-ACCESS  read-write
   STATUS      current
   DESCRIPTION
       " default:  7(Debug)
        0: Emergency
        1: Alert
        2: Critical
        3: Error
        4: Warning
        5: Notice
        6: Info
        7: Debug"
   ::= { gel2esw26kTrapEventSeverity 2 }

gel2esw26kTrapEventSeverityAccessMgmt OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 3 }

gel2esw26kTrapEventSeverityAuthFailed OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gel2esw26kTrapEventSeverity 4 }

gel2esw26kTrapEventSeverityColdStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gel2esw26kTrapEventSeverity 5 }

gel2esw26kTrapEventSeverityConfigInfo OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 6 }

gel2esw26kTrapEventSeverityFirmwareUpgrade OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 7 }

gel2esw26kTrapEventSeverityImportExport OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 8 }

gel2esw26kTrapEventSeverityLACP OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 9 }

gel2esw26kTrapEventSeverityLinkStatus OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gel2esw26kTrapEventSeverity 10 }

gel2esw26kTrapEventSeverityLogin OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 11 }

gel2esw26kTrapEventSeverityLogout OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 12 }

gel2esw26kTrapEventSeverityLoopProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 13 }

gel2esw26kTrapEventSeverityMgmtIPChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 14 }

gel2esw26kTrapEventSeverityModuleChange OBJECT-TYPE
   SYNTAX      INTEGER (0..7)
   MAX-ACCESS  read-write
   STATUS      current
   DESCRIPTION
       " default:  5(Notice)
        0: Emergency
        1: Alert
        2: Critical
        3: Error
        4: Warning
        5: Notice
        6: Info
        7: Debug"
   ::= { gel2esw26kTrapEventSeverity 15 }

gel2esw26kTrapEventSeverityNAS OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 16 }

gel2esw26kTrapEventSeverityPasswordChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 17 }

gel2esw26kTrapEventSeverityPortSecurity OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 18 }

gel2esw26kTrapEventSeverityThermalProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 19 }

gel2esw26kTrapEventSeverityVLAN OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw26kTrapEventSeverity 20 }

gel2esw26kTrapEventSeverityWarmStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gel2esw26kTrapEventSeverity 21 }


gel2esw26kSMTP                                             OBJECT IDENTIFIER ::= { gel2esw26kConfiguration 8 }

gel2esw26kSMTPMailServer OBJECT-TYPE
   SYNTAX      DisplayString
   MAX-ACCESS  read-write
   STATUS      current
   DESCRIPTION
       " Up to 47 characters describing email server. "
   ::= { gel2esw26kSMTP 1 }

gel2esw26kSMTPUserName OBJECT-TYPE
   SYNTAX      DisplayString
   MAX-ACCESS  read-write
   STATUS      current
   DESCRIPTION
       " Up to 47 characters describing user name. "
   ::= { gel2esw26kSMTP 2 }

gel2esw26kSMTPPassword OBJECT-TYPE
   SYNTAX      DisplayString
   MAX-ACCESS  read-write
   STATUS      current
   DESCRIPTION
       " Up to 47 characters describing password. "
   ::= { gel2esw26kSMTP 3 }

gel2esw26kSMTPServeriryLevel OBJECT-TYPE
   SYNTAX      INTEGER(0..7)
   MAX-ACCESS  read-write
   STATUS      current
   DESCRIPTION
       "default: 6
       0: Emergency
       1: Alert
       2: Critical
       3: Error
       4: Warning
       5: Notice
       6: Info
       7: Debug"
   ::= { gel2esw26kSMTP 4 }

gel2esw26kSMTPSender OBJECT-TYPE
   SYNTAX      DisplayString
   MAX-ACCESS  read-write
   STATUS      current
   DESCRIPTION
       " Up to 47 characters describing sender. "
   ::= { gel2esw26kSMTP 5 }

gel2esw26kSMTPReturnPath OBJECT-TYPE
   SYNTAX      DisplayString
   MAX-ACCESS  read-write
   STATUS      current
   DESCRIPTION
       " Up to 47 characters describing return path. "
   ::= { gel2esw26kSMTP 6 }

gel2esw26kSMTPEmailAddress1 OBJECT-TYPE
   SYNTAX      DisplayString
   MAX-ACCESS  read-write
   STATUS      current
   DESCRIPTION
       " Up to 47 characters describing mail address. "
   ::= { gel2esw26kSMTP 7 }

gel2esw26kSMTPEmailAddress2 OBJECT-TYPE
   SYNTAX      DisplayString
   MAX-ACCESS  read-write
   STATUS      current
   DESCRIPTION
       " Up to 47 characters describing mail address. "
   ::= { gel2esw26kSMTP 8 }

gel2esw26kSMTPEmailAddress3 OBJECT-TYPE
   SYNTAX      DisplayString
   MAX-ACCESS  read-write
   STATUS      current
   DESCRIPTION
       " Up to 47 characters describing mail address. "
   ::= { gel2esw26kSMTP 9 }

gel2esw26kSMTPEmailAddress4 OBJECT-TYPE
   SYNTAX      DisplayString
   MAX-ACCESS  read-write
   STATUS      current
   DESCRIPTION
       " Up to 47 characters describing mail address. "
   ::= { gel2esw26kSMTP 10 }

gel2esw26kSMTPEmailAddress5 OBJECT-TYPE
   SYNTAX      DisplayString
   MAX-ACCESS  read-write
   STATUS      current
   DESCRIPTION
       " Up to 47 characters describing mail address. "
   ::= { gel2esw26kSMTP 11 }

gel2esw26kSMTPEmailAddress6 OBJECT-TYPE
   SYNTAX      DisplayString
   MAX-ACCESS  read-write
   STATUS      current
   DESCRIPTION
       " Up to 47 characters describing mail address. "
   ::= { gel2esw26kSMTP 12 }


gel2esw26kACL                                                   OBJECT IDENTIFIER ::= { gel2esw26kConfiguration 9 }

gel2esw26kACLPortsConfTable OBJECT-TYPE
   SYNTAX      SEQUENCE OF GEL2ESW26KACLPortsConfEntry
   MAX-ACCESS  not-accessible
   STATUS      current
   DESCRIPTION
       " "
   ::= { gel2esw26kACL 1 }

gel2esw26kACLPortsConfEntry OBJECT-TYPE
   SYNTAX      GEL2ESW26KACLPortsConfEntry
   MAX-ACCESS  not-accessible
   STATUS      current
   DESCRIPTION
       ""
   INDEX    { gel2esw26kACLPortsConfPort  }
   ::= { gel2esw26kACLPortsConfTable 1 }

GEL2ESW26KACLPortsConfEntry ::= SEQUENCE {
   gel2esw26kACLPortsConfPort               INTEGER,
   gel2esw26kACLPortsConfPolicyID           INTEGER,
   gel2esw26kACLPortsConfAction             INTEGER,
   gel2esw26kACLPortsConfRateLimiterID      INTEGER,
   gel2esw26kACLPortsConfPortRedirect       INTEGER,
   gel2esw26kACLPortsConfMirror             INTEGER,
   gel2esw26kACLPortsConfLogging            INTEGER,
   gel2esw26kACLPortsConfShutdown           INTEGER,
   gel2esw26kACLPortsConfState              INTEGER,
   gel2esw26kACLPortsConfCounter            Counter32
}

gel2esw26kACLPortsConfPort OBJECT-TYPE
   SYNTAX      INTEGER (1..4095)
   MAX-ACCESS  not-accessible
   STATUS      current
   DESCRIPTION
       " "
   ::= { gel2esw26kACLPortsConfEntry 1 }

gel2esw26kACLPortsConfPolicyID OBJECT-TYPE
   SYNTAX      INTEGER (0..255)
   MAX-ACCESS  read-write
   STATUS      current
   DESCRIPTION
       "default: 0, range : 0 - 255 "
   ::= { gel2esw26kACLPortsConfEntry 2 }

gel2esw26kACLPortsConfAction OBJECT-TYPE
   SYNTAX      INTEGER(0|1)
   MAX-ACCESS  read-write
   STATUS      current
   DESCRIPTION
       "default: 1,
        0: Deny
        1: Permit"
   ::= { gel2esw26kACLPortsConfEntry 3 }

gel2esw26kACLPortsConfRateLimiterID OBJECT-TYPE
   SYNTAX      INTEGER (0..16)
   MAX-ACCESS  read-write
   STATUS      current
   DESCRIPTION
       "default: 0,
        0: Disable
        range : 0 - 16 "
   ::= { gel2esw26kACLPortsConfEntry 4 }

gel2esw26kACLPortsConfPortRedirect OBJECT-TYPE
   SYNTAX      INTEGER (0..4095)
   MAX-ACCESS  read-write
   STATUS      current
   DESCRIPTION
       "default: 0
        0: Disable
        range : 0 - end port number "
   ::= { gel2esw26kACLPortsConfEntry 5 }

gel2esw26kACLPortsConfMirror OBJECT-TYPE
   SYNTAX      INTEGER(0|1)
   MAX-ACCESS  read-write
   STATUS      current
   DESCRIPTION
       "default: 0
        0: Disable
        1: Enable "
   ::= { gel2esw26kACLPortsConfEntry 6 }

gel2esw26kACLPortsConfLogging OBJECT-TYPE
   SYNTAX      INTEGER(0|1)
   MAX-ACCESS  read-write
   STATUS      current
   DESCRIPTION
       "default: 0
        0: Disable
        1: Enable "
   ::= { gel2esw26kACLPortsConfEntry 7 }

gel2esw26kACLPortsConfShutdown OBJECT-TYPE
   SYNTAX      INTEGER(0|1)
   MAX-ACCESS  read-write
   STATUS      current
   DESCRIPTION
       "default: 0
        0: Disable
        1: Enable "
   ::= { gel2esw26kACLPortsConfEntry 8 }

gel2esw26kACLPortsConfState OBJECT-TYPE
   SYNTAX      INTEGER(0|1)
   MAX-ACCESS  read-write
   STATUS      current
   DESCRIPTION
       "default: 1
        0: Disable
        1: Enable "
   ::= { gel2esw26kACLPortsConfEntry 9 }

gel2esw26kACLPortsConfCounter OBJECT-TYPE
   SYNTAX      Counter32
   MAX-ACCESS  read-only
   STATUS      current
   DESCRIPTION
       "Counts the number of frames that match this ACE. "
   ::= { gel2esw26kACLPortsConfEntry 10 }


gel2esw26kACLRateLimiterTable OBJECT-TYPE
   SYNTAX      SEQUENCE OF GEL2ESW26KACLRateLimiterEntry
   MAX-ACCESS  not-accessible
   STATUS      current
   DESCRIPTION
       " "
   ::= { gel2esw26kACL 2 }

gel2esw26kACLRateLimiterEntry OBJECT-TYPE
   SYNTAX      GEL2ESW26KACLRateLimiterEntry
   MAX-ACCESS  not-accessible
   STATUS      current
   DESCRIPTION
       ""
   INDEX    { gel2esw26kACLRateLimiterID  }
   ::= { gel2esw26kACLRateLimiterTable 1 }

GEL2ESW26KACLRateLimiterEntry ::= SEQUENCE {
   gel2esw26kACLRateLimiterID       INTEGER,
   gel2esw26kACLRateLimiterUnit     INTEGER,
   gel2esw26kACLRateLimiterRate     INTEGER
}

gel2esw26kACLRateLimiterID OBJECT-TYPE
   SYNTAX      INTEGER (1..16)
   MAX-ACCESS  not-accessible
   STATUS      current
   DESCRIPTION
       " Rate Limiter ID.
         range : 1-16 "
   ::= { gel2esw26kACLRateLimiterEntry 1 }

gel2esw26kACLRateLimiterUnit OBJECT-TYPE
   SYNTAX      INTEGER(0|1)
   MAX-ACCESS  read-write
   STATUS      current
   DESCRIPTION
       "default: 0,
        0: pps
        1: kbps"
   ::= { gel2esw26kACLRateLimiterEntry 2 }

gel2esw26kACLRateLimiterRate OBJECT-TYPE
   SYNTAX      INTEGER (0..3276700)
   MAX-ACCESS  read-write
   STATUS      current
   DESCRIPTION
       "default: 1,
        range : <0-3276700> pps
                <0-10000> kbps"
   ::= { gel2esw26kACLRateLimiterEntry 3 }


gel2esw26kACLACE                                          OBJECT IDENTIFIER ::= { gel2esw26kACL 3 }

gel2esw26kACLACECreate OBJECT-TYPE
   SYNTAX       INTEGER(0|1)
   MAX-ACCESS   read-write
   STATUS       current
   DESCRIPTION
       "default: 0
        0 : None  (read only)
        1 : Create an ACE entry"
   ::= { gel2esw26kACLACE 1 }

gel2esw26kACLACETable OBJECT-TYPE
   SYNTAX      SEQUENCE OF GEL2ESW26KACLACEEntry
   MAX-ACCESS  not-accessible
   STATUS      current
   DESCRIPTION
       " Create ACL ACE entry. "
   ::= { gel2esw26kACLACE 2 }

gel2esw26kACLACEEntry OBJECT-TYPE
   SYNTAX      GEL2ESW26KACLACEEntry
   MAX-ACCESS  not-accessible
   STATUS      current
   DESCRIPTION
       ""
   INDEX    { gel2esw26kACLACEIndex  }
   ::= { gel2esw26kACLACETable 1 }

GEL2ESW26KACLACEEntry ::= SEQUENCE {
   gel2esw26kACLACEIndex                INTEGER,
   gel2esw26kACLACEID                   INTEGER,
   gel2esw26kACLACENextID               INTEGER,
   gel2esw26kACLACEIngressPort          DisplayString,
   gel2esw26kACLACEPortPolicyNumber     INTEGER,

   gel2esw26kACLACEPortPolicyBitmask    INTEGER,
   gel2esw26kACLACEFrameType            INTEGER,
   gel2esw26kACLACEAction               INTEGER,
   gel2esw26kACLACEDenyPortRedirect     DisplayString,
   gel2esw26kACLACELogging              INTEGER,

   gel2esw26kACLACEMirror               INTEGER,
   gel2esw26kACLACERateLimiter          INTEGER,
   gel2esw26kACLACEShutdown             INTEGER,
   gel2esw26kACLACEVLAN8021QTagged      INTEGER,
   gel2esw26kACLACEVLANTagPriority      INTEGER,

   gel2esw26kACLACEVLANVID              INTEGER,
   gel2esw26kACLACEEtherType            INTEGER,
   gel2esw26kACLACESMAC                 DisplayString,
   gel2esw26kACLACEDMACType             INTEGER,
   gel2esw26kACLACEDMAC                 DisplayString,

   gel2esw26kACLACEArpOpcode            INTEGER,
   gel2esw26kACLACEArpFlagsRequestReply INTEGER,
   gel2esw26kACLACEArpFlagsArpSmac      INTEGER,
   gel2esw26kACLACEArpFlagsRarpDmac     INTEGER,
   gel2esw26kACLACEArpFlagsLength       INTEGER,

   gel2esw26kACLACEArpFlagsIp           INTEGER,
   gel2esw26kACLACEArpFlagsEthernet     INTEGER,
   gel2esw26kACLACESIPType              INTEGER,
   gel2esw26kACLACESIPIPAddress         IpAddress,
   gel2esw26kACLACESIPNetworkPrefix     INTEGER,

   gel2esw26kACLACEDIPType              INTEGER,
   gel2esw26kACLACEDIPIPAddress         IpAddress,
   gel2esw26kACLACEDIPNetworkPrefix     INTEGER,

   gel2esw26kACLACEIPProtocol           INTEGER,
   gel2esw26kACLACEIPFlagsTTL           INTEGER,
   gel2esw26kACLACEIPFlagsOptions       INTEGER,
   gel2esw26kACLACEIPFlagsFragment      INTEGER,
   gel2esw26kACLACEICMPType             INTEGER,

   gel2esw26kACLACEICMPCode             INTEGER,
   gel2esw26kACLACESourcePortMin        INTEGER,
   gel2esw26kACLACESourcePortMax        INTEGER,
   gel2esw26kACLACEDestPortMin          INTEGER,
   gel2esw26kACLACEDestPortMax          INTEGER,

   gel2esw26kACLACETCPFlagsFin          INTEGER,
   gel2esw26kACLACETCPFlagsSyn          INTEGER,
   gel2esw26kACLACETCPFlagsRst          INTEGER,
   gel2esw26kACLACETCPFlagsPsh          INTEGER,
   gel2esw26kACLACETCPFlagsAck          INTEGER,

   gel2esw26kACLACETCPFlagsUrg          INTEGER,

   gel2esw26kACLACERowStatus            INTEGER
}

gel2esw26kACLACEIndex OBJECT-TYPE
   SYNTAX      INTEGER (1..256)
   MAX-ACCESS  not-accessible
   STATUS      current
   DESCRIPTION
       " "
   ::= { gel2esw26kACLACEEntry 1 }

gel2esw26kACLACEID OBJECT-TYPE
   SYNTAX      INTEGER (1..256)
   MAX-ACCESS  read-write
   STATUS      current
   DESCRIPTION
       " If the ACE ID is specified and an entry with this ACE ID
         already exists, the ACE will be modified. Otherwise, a
         new ACE will be added.
         range : 1 - 256. "
   ::= { gel2esw26kACLACEEntry 2 }

gel2esw26kACLACENextID OBJECT-TYPE
   SYNTAX      INTEGER (0..256)
   MAX-ACCESS  read-write
   STATUS      current
   DESCRIPTION
       " If the next ACE ID is non zero, the ACE will be placed
         before this ACE in the list. If the next ACE ID is zero,
         the ACE will be placed last in the list.
         range : 0 - 256. "
   ::= { gel2esw26kACLACEEntry 3 }

gel2esw26kACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { gel2esw26kACLACEEntry 4 }

gel2esw26kACLACEPortPolicyNumber OBJECT-TYPE
   SYNTAX      INTEGER (0..255)
   MAX-ACCESS  read-write
   STATUS      current
   DESCRIPTION
       " policy value.
         range : 0 - 255. "
   ::= { gel2esw26kACLACEEntry 5 }

gel2esw26kACLACEPortPolicyBitmask OBJECT-TYPE
   SYNTAX      INTEGER (0..255)
   MAX-ACCESS  read-write
   STATUS      current
   DESCRIPTION
       " policy bitmask.
         range : 0 - 255(0xff). "
   ::= { gel2esw26kACLACEEntry 6 }

gel2esw26kACLACEFrameType OBJECT-TYPE
   SYNTAX      INTEGER (0..6)
   MAX-ACCESS  read-write
   STATUS      current
   DESCRIPTION
       " 0: any,
         1: arp,
         2: etype,
         3: icmp,
         4: ipv4,
         5: tcp,
         6: udp."
   ::= { gel2esw26kACLACEEntry 7 }

gel2esw26kACLACEAction OBJECT-TYPE
   SYNTAX      INTEGER(0|1)
   MAX-ACCESS  read-write
   STATUS      current
   DESCRIPTION
       "default: 1,
        0: Deny
        1: Permit"
   ::= { gel2esw26kACLACEEntry 8 }

gel2esw26kACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { gel2esw26kACLACEEntry 9 }

gel2esw26kACLACELogging OBJECT-TYPE
   SYNTAX      INTEGER(0|1)
   MAX-ACCESS  read-write
   STATUS      current
   DESCRIPTION
       "default: 0,
        0: disable - Frames matching the ACE are not logged.
        1: enable - Frames matching the ACE are stored in the system log."
   ::= { gel2esw26kACLACEEntry 10 }

gel2esw26kACLACEMirror OBJECT-TYPE
   SYNTAX      INTEGER(0|1)
   MAX-ACCESS  read-write
   STATUS      current
   DESCRIPTION
       "default: 0,
        0: disable - Frames matching the ACE are not mirrored.
        1: enable - Frames matching the ACE are mirrored."
   ::= { gel2esw26kACLACEEntry 11 }

gel2esw26kACLACERateLimiter OBJECT-TYPE
   SYNTAX      INTEGER (0..16)
   MAX-ACCESS  read-write
   STATUS      current
   DESCRIPTION
       "default: 0,
        0: Disable
        range : 0 - 16 "
   ::= { gel2esw26kACLACEEntry 12 }

gel2esw26kACLACEShutdown OBJECT-TYPE
   SYNTAX      INTEGER(0|1)
   MAX-ACCESS  read-write
   STATUS      current
   DESCRIPTION
       "default: 0,
        0: disable - Port shut down is disabled for the AC.
        1: enable - If a frame matches the ACE, the ingress port will be disabled."
   ::= { gel2esw26kACLACEEntry 13 }

gel2esw26kACLACEVLAN8021QTagged OBJECT-TYPE
   SYNTAX      INTEGER (0..2)
   MAX-ACCESS  read-write
   STATUS      current
   DESCRIPTION
       "Specify whether frames can hit the action according to the 802.1Q tagged.
        default: 2,
        0: disable - Untagged frame only.
        1: enable - Tagged frame only.
        2: Any - Any value is allowed. "
   ::= { gel2esw26kACLACEEntry 14 }

gel2esw26kACLACEVLANTagPriority OBJECT-TYPE
   SYNTAX      INTEGER (0..8)
   MAX-ACCESS  read-write
   STATUS      current
   DESCRIPTION
       "Specify the tag priority for this ACE.
        The tag priority can't be set when 802.1Q Tagged is disabled
        default: 8,
        8: Any,
        range : 0 - 8 "
   ::= { gel2esw26kACLACEEntry 15 }

gel2esw26kACLACEVLANVID OBJECT-TYPE
   SYNTAX      INTEGER (0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { gel2esw26kACLACEEntry 16 }

gel2esw26kACLACEEtherType OBJECT-TYPE
   SYNTAX      INTEGER (0..65535)
   MAX-ACCESS  read-write
   STATUS      current
   DESCRIPTION
       " 0: Any - Any but excluding 0x0800(IPv4) 0x0806(ARP) and 0x86DD(IPv6).
         range : 0 or 1536(0x0600)- 65535(0xffff). "
   ::= { gel2esw26kACLACEEntry 17 }

gel2esw26kACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { gel2esw26kACLACEEntry 18 }

gel2esw26kACLACEDMACType OBJECT-TYPE
   SYNTAX      INTEGER (0..4)
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address
        range : 0 - 4 "
   ::= { gel2esw26kACLACEEntry 19 }

gel2esw26kACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { gel2esw26kACLACEEntry 20 }

gel2esw26kACLACEArpOpcode OBJECT-TYPE
   SYNTAX      INTEGER (0..3)
   MAX-ACCESS  read-write
   STATUS      current
   DESCRIPTION
       "Configure ARP opcode for this ACE.
        default: 0,
        0: Any - Don't care.
        1: arp.
        2: rarp.
        3: other.
        4: No data.
        range : 0 - 3 "
   ::= { gel2esw26kACLACEEntry 21 }

gel2esw26kACLACEArpFlagsRequestReply OBJECT-TYPE
   SYNTAX      INTEGER (0..2)
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 2 "
   ::= { gel2esw26kACLACEEntry 22 }

gel2esw26kACLACEArpFlagsArpSmac OBJECT-TYPE
   SYNTAX      INTEGER (0..2)
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 2 "
   ::= { gel2esw26kACLACEEntry 23 }

gel2esw26kACLACEArpFlagsRarpDmac OBJECT-TYPE
   SYNTAX      INTEGER (0..2)
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 2 "
   ::= { gel2esw26kACLACEEntry 24 }

gel2esw26kACLACEArpFlagsLength OBJECT-TYPE
   SYNTAX      INTEGER (0..2)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 2 "
   ::= { gel2esw26kACLACEEntry 25 }

gel2esw26kACLACEArpFlagsIp OBJECT-TYPE
   SYNTAX      INTEGER (0..2)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 2 "
   ::= { gel2esw26kACLACEEntry 26 }

gel2esw26kACLACEArpFlagsEthernet OBJECT-TYPE
   SYNTAX      INTEGER (0..2)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 2 "
   ::= { gel2esw26kACLACEEntry 27 }

gel2esw26kACLACESIPType OBJECT-TYPE
   SYNTAX      INTEGER(0|1)
   MAX-ACCESS  read-write
   STATUS      current
   DESCRIPTION
       "Configure source IP address for this ACE.
        default: 0,
        0: Any - Don't care.
        1: IP Address.
        2: No data.
        range : 0 - 1"
   ::= { gel2esw26kACLACEEntry 28 }

gel2esw26kACLACESIPIPAddress OBJECT-TYPE
   SYNTAX      IpAddress
   MAX-ACCESS  read-write
   STATUS      current
   DESCRIPTION
       "A frame that hits this ACE matches this source IP address value."
   ::= { gel2esw26kACLACEEntry 29 }

gel2esw26kACLACESIPNetworkPrefix OBJECT-TYPE
   SYNTAX      INTEGER (1..32)
   MAX-ACCESS  read-write
   STATUS      current
   DESCRIPTION
       "Network prefix.
        default: 32,
        0: No data.
        range : 1 - 32"
   ::= { gel2esw26kACLACEEntry 30 }


gel2esw26kACLACEDIPType OBJECT-TYPE
   SYNTAX      INTEGER(0|1)
   MAX-ACCESS  read-write
   STATUS      current
   DESCRIPTION
       "Configure destination IP address for this ACE.
        default: 0,
        0: Any - Don't care.
        1: IP Address.
        2: No data.
        range : 0 - 1"
   ::= { gel2esw26kACLACEEntry 32 }

gel2esw26kACLACEDIPIPAddress OBJECT-TYPE
   SYNTAX      IpAddress
   MAX-ACCESS  read-write
   STATUS      current
   DESCRIPTION
       "A frame that hits this ACE matches this destination IP address value."
   ::= { gel2esw26kACLACEEntry 33 }

gel2esw26kACLACEDIPNetworkPrefix OBJECT-TYPE
   SYNTAX      INTEGER (1..32)
   MAX-ACCESS  read-write
   STATUS      current
   DESCRIPTION
       "Network prefix.
        default: 32,
        0: No data.
        range : 1 - 32"
   ::= { gel2esw26kACLACEEntry 34 }


gel2esw26kACLACEIPProtocol OBJECT-TYPE
   SYNTAX      INTEGER (0..256)
   MAX-ACCESS  read-write
   STATUS      current
   DESCRIPTION
       "Configure IP protocol for this ACE.
        default: 256,
        256: Any - Don't care.
        257: No data.
        range : 0 - 256"
   ::= { gel2esw26kACLACEEntry 36 }

gel2esw26kACLACEIPFlagsTTL OBJECT-TYPE
   SYNTAX      INTEGER (0..2)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 2 "
   ::= { gel2esw26kACLACEEntry 37 }

gel2esw26kACLACEIPFlagsOptions OBJECT-TYPE
   SYNTAX      INTEGER (0..2)
   MAX-ACCESS  read-write
   STATUS      current
   DESCRIPTION
       "Configure IP options flag for this ACE.
        default: 2,
        0: IPv4 frames where the options flag is unset.
        1: IPv4 frames where the options flag is set.
        2: Any - Don't care.
        3: No data.
        range : 0 - 2 "
   ::= { gel2esw26kACLACEEntry 38 }

gel2esw26kACLACEIPFlagsFragment OBJECT-TYPE
   SYNTAX      INTEGER (0..2)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 2 "
   ::= { gel2esw26kACLACEEntry 39 }

gel2esw26kACLACEICMPType OBJECT-TYPE
   SYNTAX      INTEGER (0..256)
   MAX-ACCESS  read-write
   STATUS      current
   DESCRIPTION
       "Configure ICMP type for this ACE.
        default: 256,
        256: Any - Don't care.
        257: No data.
        range : 0 - 256"
   ::= { gel2esw26kACLACEEntry 40 }

gel2esw26kACLACEICMPCode OBJECT-TYPE
   SYNTAX      INTEGER (0..256)
   MAX-ACCESS  read-write
   STATUS      current
   DESCRIPTION
       "Configure ICMP code for this ACE.
        default: 256,
        256: Any - Don't care.
        257: No data.
        range : 0 - 256"
   ::= { gel2esw26kACLACEEntry 41 }

gel2esw26kACLACESourcePortMin OBJECT-TYPE
   SYNTAX      INTEGER (0..65535)
   MAX-ACCESS  read-write
   STATUS      current
   DESCRIPTION
       "Configure Source UDP/TCP port range for this ACE.
        default: 0,
        65536: No data.
        range : 0 - 65535"
   ::= { gel2esw26kACLACEEntry 42 }

gel2esw26kACLACESourcePortMax OBJECT-TYPE
   SYNTAX      INTEGER (0..65535)
   MAX-ACCESS  read-write
   STATUS      current
   DESCRIPTION
       "Configure Source UDP/TCP port range for this ACE.
        default: 0,
        65536: No data.
        range : 0 - 65535"
   ::= { gel2esw26kACLACEEntry 43 }

gel2esw26kACLACEDestPortMin OBJECT-TYPE
   SYNTAX      INTEGER (0..65535)
   MAX-ACCESS  read-write
   STATUS      current
   DESCRIPTION
       "Configure Destination UDP/TCP port range for this ACE.
        default: 0,
        65536: No data.
        range : 0 - 65535"
   ::= { gel2esw26kACLACEEntry 44 }

gel2esw26kACLACEDestPortMax OBJECT-TYPE
   SYNTAX      INTEGER (0..65535)
   MAX-ACCESS  read-write
   STATUS      current
   DESCRIPTION
       "Configure Destination UDP/TCP port range for this ACE.
        default: 0,
        65536: No data.
        range : 0 - 65535"
   ::= { gel2esw26kACLACEEntry 45 }

gel2esw26kACLACETCPFlagsFin OBJECT-TYPE
   SYNTAX      INTEGER (0..2)
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 2 "
   ::= { gel2esw26kACLACEEntry 46 }

gel2esw26kACLACETCPFlagsSyn OBJECT-TYPE
   SYNTAX      INTEGER (0..2)
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 2 "
   ::= { gel2esw26kACLACEEntry 47 }

gel2esw26kACLACETCPFlagsRst OBJECT-TYPE
   SYNTAX      INTEGER (0..2)
   MAX-ACCESS  read-write
   STATUS      current
   DESCRIPTION
       "Configure TCP (RST) flags for this ACE.
        default: 2,
        0: TCP frames where the RST field is unset.
        1: TCP frames where the RST field is set.
        2: Any - Don't care.
        3: No data.
        range : 0 - 2 "
   ::= { gel2esw26kACLACEEntry 48 }

gel2esw26kACLACETCPFlagsPsh OBJECT-TYPE
   SYNTAX      INTEGER (0..2)
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 2 "
   ::= { gel2esw26kACLACEEntry 49 }

gel2esw26kACLACETCPFlagsAck OBJECT-TYPE
   SYNTAX      INTEGER (0..2)
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 2 "
   ::= { gel2esw26kACLACEEntry 50 }

gel2esw26kACLACETCPFlagsUrg OBJECT-TYPE
   SYNTAX      INTEGER (0..2)
   MAX-ACCESS  read-write
   STATUS      current
   DESCRIPTION
       "Configure TCP (URG) flags for this ACE.
        default: 2,
        0: TCP frames where the URG field is unset.
        1: TCP frames where the URG field is set.
        2: Any - Don't care.
        3: No data.
        range : 0 - 2 "
   ::= { gel2esw26kACLACEEntry 51 }

gel2esw26kACLACERowStatus OBJECT-TYPE
   SYNTAX      INTEGER (1..5)
   MAX-ACCESS  read-write
   STATUS      current
   DESCRIPTION
       " 1: active
         2: notInservice
         4: destroy
         5: undo"
   ::= { gel2esw26kACLACEEntry 66 }


gel2esw26kACLACEClear OBJECT-TYPE
   SYNTAX       INTEGER(0|1)
   MAX-ACCESS   read-write
   STATUS       current
   DESCRIPTION
       "default: 0
        0 : No action
        1 : Clear all ACL counters."
   ::= { gel2esw26kACLACE 3 }

gel2esw26kACLACEMoveACEID OBJECT-TYPE
   SYNTAX       INTEGER (1..256)
   MAX-ACCESS   read-write
   STATUS       current
   DESCRIPTION
       "Move ACE,
        default: 0
        ACE ID must be exist.
        range : 1 - 256."
   ::= { gel2esw26kACLACE 4 }

gel2esw26kACLACEMoveNextACEID OBJECT-TYPE
   SYNTAX       INTEGER (0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gel2esw26kACLACE 5 }

gel2esw26kACLACEStatusTable OBJECT-TYPE
   SYNTAX      SEQUENCE OF GEL2ESW26KACLACEStatusEntry
   MAX-ACCESS  not-accessible
   STATUS      current
   DESCRIPTION
       " ACL ACE Status entry. "
   ::= { gel2esw26kACLACE 6 }

gel2esw26kACLACEStatusEntry OBJECT-TYPE
   SYNTAX      GEL2ESW26KACLACEStatusEntry
   MAX-ACCESS  not-accessible
   STATUS      current
   DESCRIPTION
       ""
   INDEX    { gel2esw26kACLACEStatusIndex  }
   ::= { gel2esw26kACLACEStatusTable 1 }

GEL2ESW26KACLACEStatusEntry ::= SEQUENCE {
   gel2esw26kACLACEStatusIndex          INTEGER,
   gel2esw26kACLACEStatusUser           DisplayString,
   gel2esw26kACLACEStatusID             INTEGER,
   gel2esw26kACLACEStatusIngressPort    DisplayString,
   gel2esw26kACLACEStatusFrameType      DisplayString,
   gel2esw26kACLACEStatusAction         DisplayString,
   gel2esw26kACLACEStatusRateLimiter    DisplayString,
   gel2esw26kACLACEStatusPortCopy       DisplayString,
   gel2esw26kACLACEStatusMirror         DisplayString,
   gel2esw26kACLACEStatusCPU            DisplayString,
   gel2esw26kACLACEStatusCounter        Counter32,
   gel2esw26kACLACEStatusConflict       DisplayString
}

gel2esw26kACLACEStatusIndex OBJECT-TYPE
   SYNTAX      INTEGER (1..256)
   MAX-ACCESS  not-accessible
   STATUS      current
   DESCRIPTION
       " "
   ::= { gel2esw26kACLACEStatusEntry 1 }

gel2esw26kACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { gel2esw26kACLACEStatusEntry 2 }

gel2esw26kACLACEStatusID OBJECT-TYPE
   SYNTAX      INTEGER (1..256)
   MAX-ACCESS  read-only
   STATUS      current
   DESCRIPTION
       " ACE ID.
         range : 1 - 256. "
   ::= { gel2esw26kACLACEStatusEntry 3 }

gel2esw26kACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { gel2esw26kACLACEStatusEntry 4 }

gel2esw26kACLACEStatusFrameType OBJECT-TYPE
   SYNTAX      DisplayString
   MAX-ACCESS  read-only
   STATUS      current
   DESCRIPTION
       " Indicates the frame type of the ACE. "
   ::= { gel2esw26kACLACEStatusEntry 5 }

gel2esw26kACLACEStatusAction OBJECT-TYPE
   SYNTAX      DisplayString
   MAX-ACCESS  read-only
   STATUS      current
   DESCRIPTION
       " Indicates the forwarding action of the ACE. "
   ::= { gel2esw26kACLACEStatusEntry 6 }

gel2esw26kACLACEStatusRateLimiter OBJECT-TYPE
   SYNTAX      DisplayString
   MAX-ACCESS  read-only
   STATUS      current
   DESCRIPTION
       " Indicates the rate limiter number of the ACE. "
   ::= { gel2esw26kACLACEStatusEntry 7 }

gel2esw26kACLACEStatusPortCopy OBJECT-TYPE
   SYNTAX      DisplayString
   MAX-ACCESS  read-only
   STATUS      current
   DESCRIPTION
       " Indicates the port redirect operation of the ACE. Frames matching the ACE are redirected to the port number. "
   ::= { gel2esw26kACLACEStatusEntry 8 }

gel2esw26kACLACEStatusMirror OBJECT-TYPE
   SYNTAX      DisplayString
   MAX-ACCESS  read-only
   STATUS      current
   DESCRIPTION
       " Specify the mirror operation of this port. "
   ::= { gel2esw26kACLACEStatusEntry 9 }

gel2esw26kACLACEStatusCPU OBJECT-TYPE
   SYNTAX      DisplayString
   MAX-ACCESS  read-only
   STATUS      current
   DESCRIPTION
       " Forward packet that matched the specific ACE to CPU. "
   ::= { gel2esw26kACLACEStatusEntry 10 }

gel2esw26kACLACEStatusCounter OBJECT-TYPE
   SYNTAX      Counter32
   MAX-ACCESS  read-only
   STATUS      current
   DESCRIPTION
       " The counter indicates the number of times the ACE was hit by a frame. "
   ::= { gel2esw26kACLACEStatusEntry 11 }

gel2esw26kACLACEStatusConflict OBJECT-TYPE
   SYNTAX      DisplayString
   MAX-ACCESS  read-only
   STATUS      current
   DESCRIPTION
       " Indicates the hardware status of the specific ACE. The specific ACE is not applied to the hardware due to hardware limitations. "
   ::= { gel2esw26kACLACEStatusEntry 12 }

gel2esw26kLoopProtection                                                  OBJECT IDENTIFIER ::= { gel2esw26kConfiguration 12 }

gel2esw26kLoopProtectionConfig                                            OBJECT IDENTIFIER ::= { gel2esw26kLoopProtection 1 }

gel2esw26kLoopProtectionGlobalEnable OBJECT-TYPE
   SYNTAX      INTEGER(0|1)
   MAX-ACCESS  read-write
   STATUS      current
   DESCRIPTION
       "Configure loop protection mode.
        0: disable,
        1: enable,
        default: disable. "
   ::= { gel2esw26kLoopProtectionConfig 1 }

gel2esw26kLoopProtectionTranmisstionTime OBJECT-TYPE
   SYNTAX      INTEGER(1..10)
   MAX-ACCESS  read-write
   STATUS      current
   DESCRIPTION
       "Configure loop protection transmit interval.
        default: 5,
        range: 1-10. "
   ::= { gel2esw26kLoopProtectionConfig 2 }

gel2esw26kLoopProtectionShutdownTime OBJECT-TYPE
   SYNTAX      INTEGER(0..604800)
   MAX-ACCESS  read-write
   STATUS      current
   DESCRIPTION
       "Configure loop protection shutdown time.
        default: 180,
        range: 0-604800. "
   ::= { gel2esw26kLoopProtectionConfig 3 }

gel2esw26kLoopProtectionConfigurationTable OBJECT-TYPE
   SYNTAX      SEQUENCE OF GEL2ESW26KLoopProtectionConfigurationEntry
   MAX-ACCESS  not-accessible
   STATUS      current
   DESCRIPTION
       " Show Loop Protection configurations. "
   ::= { gel2esw26kLoopProtectionConfig 4 }

gel2esw26kLoopProtectionConfigurationEntry OBJECT-TYPE
   SYNTAX      GEL2ESW26KLoopProtectionConfigurationEntry
   MAX-ACCESS  not-accessible
   STATUS      current
   DESCRIPTION
       ""
   INDEX    { gel2esw26kLoopProtectionConfPort  }
   ::= { gel2esw26kLoopProtectionConfigurationTable 1 }

GEL2ESW26KLoopProtectionConfigurationEntry ::= SEQUENCE {
   gel2esw26kLoopProtectionConfPort	    INTEGER,
   gel2esw26kLoopProtectionConfEnable	INTEGER,
   gel2esw26kLoopProtectionConfAction	INTEGER,
   gel2esw26kLoopProtectionConfTxmode	INTEGER
}

gel2esw26kLoopProtectionConfPort OBJECT-TYPE
   SYNTAX      INTEGER (1..4095)
   MAX-ACCESS  not-accessible
   STATUS      current
   DESCRIPTION
       " port, range : 1 - port number. "
   ::= { gel2esw26kLoopProtectionConfigurationEntry 1 }

gel2esw26kLoopProtectionConfEnable OBJECT-TYPE
   SYNTAX      INTEGER(0|1)
   MAX-ACCESS  read-write
   STATUS      current
   DESCRIPTION
       "Configure loop protection port mode.
        0: disable,
        1: enable,
        default: enable. "
   ::= { gel2esw26kLoopProtectionConfigurationEntry 2 }

gel2esw26kLoopProtectionConfAction OBJECT-TYPE
   SYNTAX      INTEGER(0..2)
   MAX-ACCESS  read-write
   STATUS      current
   DESCRIPTION
       " Configure loop protection port action.
         0: Shutdown port,
         1: Shutdown port and Log,
         2: Log Only,
         default: Shutdown port. "
   ::= { gel2esw26kLoopProtectionConfigurationEntry 3 }

gel2esw26kLoopProtectionConfTxmode OBJECT-TYPE
   SYNTAX      INTEGER(0|1)
   MAX-ACCESS  read-write
   STATUS      current
   DESCRIPTION
       "Configure loop protection port transmit mode.
        0: disable,
        1: enable,
        default: enable. "
   ::= { gel2esw26kLoopProtectionConfigurationEntry 4 }

gel2esw26kLoopProtectionStatusTable OBJECT-TYPE
   SYNTAX      SEQUENCE OF GEL2ESW26KLoopProtectionStatusEntry
   MAX-ACCESS  not-accessible
   STATUS      current
   DESCRIPTION
       " Show Loop Protection Status. "
   ::= { gel2esw26kLoopProtection 2 }

gel2esw26kLoopProtectionStatusEntry OBJECT-TYPE
   SYNTAX      GEL2ESW26KLoopProtectionStatusEntry
   MAX-ACCESS  not-accessible
   STATUS      current
   DESCRIPTION
       ""
   INDEX    { gel2esw26kLoopProtectionStatusPort  }
   ::= { gel2esw26kLoopProtectionStatusTable 1 }

GEL2ESW26KLoopProtectionStatusEntry ::= SEQUENCE {
   gel2esw26kLoopProtectionStatusPort	       INTEGER,
   gel2esw26kLoopProtectionStatusAction	       DisplayString,
   gel2esw26kLoopProtectionStatusTransmit	   DisplayString,
   gel2esw26kLoopProtectionStatusLoops	       INTEGER,
   gel2esw26kLoopProtectionStatusStatus	       DisplayString,
   gel2esw26kLoopProtectionStatusLoop	       DisplayString,
   gel2esw26kLoopProtectionStatusTimeLastLoop  DisplayString
}

gel2esw26kLoopProtectionStatusPort OBJECT-TYPE
   SYNTAX      INTEGER (1..4095)
   MAX-ACCESS  not-accessible
   STATUS      current
   DESCRIPTION
       " port, range : 1 - port number. "
   ::= { gel2esw26kLoopProtectionStatusEntry 1 }

gel2esw26kLoopProtectionStatusAction OBJECT-TYPE
   SYNTAX      DisplayString
   MAX-ACCESS  read-only
   STATUS      current
   DESCRIPTION
       " The currently configured port action. "
   ::= { gel2esw26kLoopProtectionStatusEntry 2 }

gel2esw26kLoopProtectionStatusTransmit OBJECT-TYPE
   SYNTAX      DisplayString
   MAX-ACCESS  read-only
   STATUS      current
   DESCRIPTION
       " The currently configured port transmit mode. "
   ::= { gel2esw26kLoopProtectionStatusEntry 3 }

gel2esw26kLoopProtectionStatusLoops OBJECT-TYPE
   SYNTAX      INTEGER (0..1000000)
   MAX-ACCESS  read-only
   STATUS      current
   DESCRIPTION
       " The number of loops detected on this port. "
   ::= { gel2esw26kLoopProtectionStatusEntry 4 }

gel2esw26kLoopProtectionStatusStatus OBJECT-TYPE
   SYNTAX      DisplayString
   MAX-ACCESS  read-only
   STATUS      current
   DESCRIPTION
       " The current loop protection status of the port. "
   ::= { gel2esw26kLoopProtectionStatusEntry 5 }

gel2esw26kLoopProtectionStatusLoop OBJECT-TYPE
   SYNTAX      DisplayString
   MAX-ACCESS  read-only
   STATUS      current
   DESCRIPTION
       " Whether a loop is currently detected on the port. "
   ::= { gel2esw26kLoopProtectionStatusEntry 6 }

gel2esw26kLoopProtectionStatusTimeLastLoop OBJECT-TYPE
   SYNTAX      DisplayString
   MAX-ACCESS  read-only
   STATUS      current
   DESCRIPTION
       " The time of the last loop event detected. "
   ::= { gel2esw26kLoopProtectionStatusEntry 7 }
----------------------------------------------------------------------------------------------------------------------------
gel2esw26kSecurity                                              OBJECT IDENTIFIER ::= { gel2esw26kProductId 3 }

gel2esw26kIPSourceGuard                                         OBJECT IDENTIFIER ::= { gel2esw26kSecurity 1 }

gel2esw26kIPSourceGuardConf                                     OBJECT IDENTIFIER ::= { gel2esw26kIPSourceGuard 1 }

gel2esw26kIPSourceGuardMode OBJECT-TYPE
   SYNTAX      INTEGER (0|1)
   MAX-ACCESS  read-write
   STATUS      current
   DESCRIPTION
       " default:  0
        0: disable
        1: enable"
   ::= { gel2esw26kIPSourceGuardConf 1 }

gel2esw26kIPSourceGuardPortConfigTable OBJECT-TYPE
   SYNTAX      SEQUENCE OF GEL2ESW26KIPSourceGuardPortConfigEntry
   MAX-ACCESS  not-accessible
   STATUS      current
   DESCRIPTION
       " "
   ::= { gel2esw26kIPSourceGuardConf 2 }

gel2esw26kIPSourceGuardPortConfigEntry OBJECT-TYPE
   SYNTAX      GEL2ESW26KIPSourceGuardPortConfigEntry
   MAX-ACCESS  not-accessible
   STATUS      current
   DESCRIPTION
       ""
   INDEX    { gel2esw26kIPSourceGuardPortConfigPort  }
   ::= { gel2esw26kIPSourceGuardPortConfigTable 1 }

GEL2ESW26KIPSourceGuardPortConfigEntry ::= SEQUENCE {
   gel2esw26kIPSourceGuardPortConfigPort               INTEGER,
   gel2esw26kIPSourceGuardPortConfigMode               INTEGER,
   gel2esw26kIPSourceGuardPortMaxDynamicClients        INTEGER
}

gel2esw26kIPSourceGuardPortConfigPort OBJECT-TYPE
   SYNTAX      INTEGER (1..4095)
   MAX-ACCESS  not-accessible
   STATUS      current
   DESCRIPTION
       " "
   ::= { gel2esw26kIPSourceGuardPortConfigEntry 1 }

gel2esw26kIPSourceGuardPortConfigMode OBJECT-TYPE
   SYNTAX      INTEGER (0|1)
   MAX-ACCESS  read-write
   STATUS      current
   DESCRIPTION
       "default: 0
       0:disable
       1:enable "
   ::= { gel2esw26kIPSourceGuardPortConfigEntry 2 }

gel2esw26kIPSourceGuardPortMaxDynamicClients OBJECT-TYPE
   SYNTAX      INTEGER (0..2|99)
   MAX-ACCESS  read-write
   STATUS      current
   DESCRIPTION
       "default: 99
       0~2: Max Dynamic clients
       99:Unlimited "
   ::= { gel2esw26kIPSourceGuardPortConfigEntry 3 }


gel2esw26kIPSourceGuardStatic                                OBJECT IDENTIFIER ::= { gel2esw26kIPSourceGuard 2 }

gel2esw26kIPSourceGuardStaticCreate OBJECT-TYPE
   SYNTAX       INTEGER(0|1)
   MAX-ACCESS   read-write
   STATUS       current
   DESCRIPTION
       "default: 0
        0 : None  (read only)
        1 : Create a IP Source Guard"
   ::= { gel2esw26kIPSourceGuardStatic 1 }

gel2esw26kIPSourceGuardStaticTable OBJECT-TYPE
   SYNTAX      SEQUENCE OF GEL2ESW26KIPSourceGuardStaticEntry
   MAX-ACCESS  not-accessible
   STATUS      current
   DESCRIPTION
       " "
   ::= { gel2esw26kIPSourceGuardStatic 2 }

gel2esw26kIPSourceGuardStaticEntry OBJECT-TYPE
   SYNTAX      GEL2ESW26KIPSourceGuardStaticEntry
   MAX-ACCESS  not-accessible
   STATUS      current
   DESCRIPTION
       ""
   INDEX    { gel2esw26kIPSourceGuardStaticIndex  }
   ::= { gel2esw26kIPSourceGuardStaticTable 1 }

GEL2ESW26KIPSourceGuardStaticEntry ::= SEQUENCE {
   gel2esw26kIPSourceGuardStaticIndex         INTEGER,
   gel2esw26kIPSourceGuardStaticPort          INTEGER,
   gel2esw26kIPSourceGuardStaticVLANId        INTEGER,
   gel2esw26kIPSourceGuardStaticIPAddress     IpAddress,
   gel2esw26kIPSourceGuardStaticMACAddress    MacAddress,
   gel2esw26kIPSourceGuardStaticRowStatus     INTEGER
}

gel2esw26kIPSourceGuardStaticIndex OBJECT-TYPE
   SYNTAX      INTEGER (1..28)
   MAX-ACCESS  not-accessible
   STATUS      current
   DESCRIPTION
       " "
   ::= { gel2esw26kIPSourceGuardStaticEntry 1 }

gel2esw26kIPSourceGuardStaticPort OBJECT-TYPE
   SYNTAX      INTEGER (1..4095)
   MAX-ACCESS  read-write
   STATUS      current
   DESCRIPTION
       " Port, range: 1 - port number. "
   ::= { gel2esw26kIPSourceGuardStaticEntry 2 }

gel2esw26kIPSourceGuardStaticVLANId OBJECT-TYPE
   SYNTAX      INTEGER (1..4094)
   MAX-ACCESS  read-write
   STATUS      current
   DESCRIPTION
       " VLAN ID, range: 1 - 4094. "
   ::= { gel2esw26kIPSourceGuardStaticEntry 3 }

gel2esw26kIPSourceGuardStaticIPAddress OBJECT-TYPE
   SYNTAX      IpAddress
   MAX-ACCESS  read-write
   STATUS      current
   DESCRIPTION
       " IP address allowed for doing IP source guard. "
   ::= { gel2esw26kIPSourceGuardStaticEntry 4 }

gel2esw26kIPSourceGuardStaticMACAddress OBJECT-TYPE
   SYNTAX      MacAddress
   MAX-ACCESS  read-write
   STATUS      current
   DESCRIPTION
       " Allowed Source MAC address, format 0a 1b 2c 3d 4e 5f "
   ::= { gel2esw26kIPSourceGuardStaticEntry 5 }

gel2esw26kIPSourceGuardStaticRowStatus OBJECT-TYPE
   SYNTAX      INTEGER (1..5)
   MAX-ACCESS  read-write
   STATUS      current
   DESCRIPTION
       "1: active
        2: notInservice
        3: edit
        4: destroy
        5: undo"
   ::= { gel2esw26kIPSourceGuardStaticEntry 6 }

gel2esw26kIPSourceGuardDynamicTable OBJECT-TYPE
   SYNTAX      SEQUENCE OF GEL2ESW26KIPSourceGuardDynamicEntry
   MAX-ACCESS  not-accessible
   STATUS      current
   DESCRIPTION
       " "
   ::= { gel2esw26kIPSourceGuard 3 }

gel2esw26kIPSourceGuardDynamicEntry OBJECT-TYPE
   SYNTAX      GEL2ESW26KIPSourceGuardDynamicEntry
   MAX-ACCESS  not-accessible
   STATUS      current
   DESCRIPTION
       ""
   INDEX    { gel2esw26kIPSourceGuardDynamicIndex  }
   ::= { gel2esw26kIPSourceGuardDynamicTable 1 }

GEL2ESW26KIPSourceGuardDynamicEntry ::= SEQUENCE {
   gel2esw26kIPSourceGuardDynamicIndex          INTEGER,
   gel2esw26kIPSourceGuardDynamicPort           INTEGER,
   gel2esw26kIPSourceGuardDynamicVLANId         INTEGER,
   gel2esw26kIPSourceGuardDynamicIPAddress      IpAddress,
   gel2esw26kIPSourceGuardDynamicMACAddress     MacAddress
}

gel2esw26kIPSourceGuardDynamicIndex OBJECT-TYPE
   SYNTAX      INTEGER(1..4095)
   MAX-ACCESS  not-accessible
   STATUS      current
   DESCRIPTION
       " "
   ::= { gel2esw26kIPSourceGuardDynamicEntry 1 }

gel2esw26kIPSourceGuardDynamicPort OBJECT-TYPE
   SYNTAX      INTEGER (1..10)
   MAX-ACCESS  read-only
   STATUS      current
   DESCRIPTION
       " "
   ::= { gel2esw26kIPSourceGuardDynamicEntry 2 }

gel2esw26kIPSourceGuardDynamicVLANId OBJECT-TYPE
   SYNTAX      INTEGER (1..4094)
   MAX-ACCESS  read-only
   STATUS      current
   DESCRIPTION
       " "
   ::= { gel2esw26kIPSourceGuardDynamicEntry 3 }

gel2esw26kIPSourceGuardDynamicIPAddress OBJECT-TYPE
   SYNTAX      IpAddress
   MAX-ACCESS  read-only
   STATUS      current
   DESCRIPTION
       " "
   ::= { gel2esw26kIPSourceGuardDynamicEntry 4 }

gel2esw26kIPSourceGuardDynamicMACAddress OBJECT-TYPE
   SYNTAX      MacAddress
   MAX-ACCESS  read-only
   STATUS      current
   DESCRIPTION
       " "
   ::= { gel2esw26kIPSourceGuardDynamicEntry 5 }

gel2esw26kARPInspection                                         OBJECT IDENTIFIER ::= { gel2esw26kSecurity 2 }

gel2esw26kARPInspectionConf                                     OBJECT IDENTIFIER ::= { gel2esw26kARPInspection 1 }

gel2esw26kARPInspectionConfMode OBJECT-TYPE
   SYNTAX      INTEGER(0|1)
   MAX-ACCESS  read-write
   STATUS      current
   DESCRIPTION
       "default: 0
        0: disable
        1: enable"
   ::= { gel2esw26kARPInspectionConf 1 }

gel2esw26kARPInspectionConfTable OBJECT-TYPE
   SYNTAX      SEQUENCE OF GEL2ESW26KARPInspectionConfEntry
   MAX-ACCESS  not-accessible
   STATUS      current
   DESCRIPTION
       " "
   ::= { gel2esw26kARPInspectionConf 2 }

gel2esw26kARPInspectionConfEntry OBJECT-TYPE
   SYNTAX      GEL2ESW26KARPInspectionConfEntry
   MAX-ACCESS  not-accessible
   STATUS      current
   DESCRIPTION
       ""
   INDEX    { gel2esw26kARPInspectionConfPortIndex  }
   ::= { gel2esw26kARPInspectionConfTable 1 }

GEL2ESW26KARPInspectionConfEntry ::= SEQUENCE {
   gel2esw26kARPInspectionConfPortIndex	INTEGER,
   gel2esw26kARPInspectionConfPortMode	INTEGER
}

gel2esw26kARPInspectionConfPortIndex OBJECT-TYPE
   SYNTAX      INTEGER(1..4095)
   MAX-ACCESS  not-accessible
   STATUS      current
   DESCRIPTION
       " "
   ::= { gel2esw26kARPInspectionConfEntry 1 }

gel2esw26kARPInspectionConfPortMode OBJECT-TYPE
   SYNTAX      INTEGER (0|1)
   MAX-ACCESS  read-write
   STATUS      current
   DESCRIPTION
       "default: 0
        0: disable
        1: enable"
   ::= { gel2esw26kARPInspectionConfEntry 2 }


gel2esw26kARPInspectionStatic                                OBJECT IDENTIFIER ::= { gel2esw26kARPInspection 2 }

gel2esw26kARPInspectionStaticCreate OBJECT-TYPE
   SYNTAX      INTEGER (0|1)
   MAX-ACCESS  read-write
   STATUS      current
   DESCRIPTION
       "default: 0
        0: none
        1: create"
   ::= { gel2esw26kARPInspectionStatic 1 }

gel2esw26kARPInspectionStaticTable OBJECT-TYPE
   SYNTAX      SEQUENCE OF GEL2ESW26KARPInspectionStaticEntry
   MAX-ACCESS  not-accessible
   STATUS      current
   DESCRIPTION
       " "
   ::= { gel2esw26kARPInspectionStatic 2 }

gel2esw26kARPInspectionStaticEntry OBJECT-TYPE
   SYNTAX      GEL2ESW26KARPInspectionStaticEntry
   MAX-ACCESS  not-accessible
   STATUS      current
   DESCRIPTION
       ""
   INDEX    { gel2esw26kARPInspectionStaticIndex  }
   ::= { gel2esw26kARPInspectionStaticTable 1 }

GEL2ESW26KARPInspectionStaticEntry ::= SEQUENCE {
   gel2esw26kARPInspectionStaticIndex       INTEGER,
   gel2esw26kARPInspectionStaticPort        INTEGER,
   gel2esw26kARPInspectionStaticVLANId      INTEGER,
   gel2esw26kARPInspectionStaticIPAddress   IpAddress,
   gel2esw26kARPInspectionStaticMACAddress  MacAddress,
   gel2esw26kARPInspectionStaticRowStatus   INTEGER
}

gel2esw26kARPInspectionStaticIndex OBJECT-TYPE
   SYNTAX      INTEGER(1..4095)
   MAX-ACCESS  not-accessible
   STATUS      current
   DESCRIPTION
       ""
   ::= { gel2esw26kARPInspectionStaticEntry 1 }

gel2esw26kARPInspectionStaticPort OBJECT-TYPE
   SYNTAX      INTEGER(1..4095)
   MAX-ACCESS  read-write
   STATUS      current
   DESCRIPTION
       " Port, range: 1 - port number. "
   ::= { gel2esw26kARPInspectionStaticEntry 2 }

gel2esw26kARPInspectionStaticVLANId OBJECT-TYPE
   SYNTAX      INTEGER (1..4094)
   MAX-ACCESS  read-write
   STATUS      current
   DESCRIPTION
       " VLAN ID, range: 1 - 4094. "
   ::= { gel2esw26kARPInspectionStaticEntry 3 }

gel2esw26kARPInspectionStaticIPAddress OBJECT-TYPE
   SYNTAX      IpAddress
   MAX-ACCESS  read-write
   STATUS      current
   DESCRIPTION
       " IP address allowed for doing ARP request. "
   ::= { gel2esw26kARPInspectionStaticEntry 4 }

gel2esw26kARPInspectionStaticMACAddress OBJECT-TYPE
   SYNTAX      MacAddress
   MAX-ACCESS  read-write
   STATUS      current
   DESCRIPTION
       " Allowed Source MAC address in ARP request packets, format 0a 1b 2c 3d 4e 5f "
   ::= { gel2esw26kARPInspectionStaticEntry 5 }

gel2esw26kARPInspectionStaticRowStatus OBJECT-TYPE
   SYNTAX      INTEGER(1..5)
   MAX-ACCESS  read-write
   STATUS      current
   DESCRIPTION
       "1: active
        2: notInservice
        3: edit
        4: destroy
        5: undo"
   ::= { gel2esw26kARPInspectionStaticEntry 6 }

gel2esw26kARPInspectionDynamicTable OBJECT-TYPE
   SYNTAX      SEQUENCE OF GEL2ESW26KARPInspectionDynamicEntry
   MAX-ACCESS  not-accessible
   STATUS      current
   DESCRIPTION
       " "
   ::= { gel2esw26kARPInspection 3 }

gel2esw26kARPInspectionDynamicEntry OBJECT-TYPE
   SYNTAX      GEL2ESW26KARPInspectionDynamicEntry
   MAX-ACCESS  not-accessible
   STATUS      current
   DESCRIPTION
       ""
   INDEX    { gel2esw26kARPInspectionDynamicIndex  }
   ::= { gel2esw26kARPInspectionDynamicTable 1 }

GEL2ESW26KARPInspectionDynamicEntry ::= SEQUENCE {
   gel2esw26kARPInspectionDynamicIndex          INTEGER,
   gel2esw26kARPInspectionDynamicPort           INTEGER,
   gel2esw26kARPInspectionDynamicVLANId         INTEGER,
   gel2esw26kARPInspectionDynamicIPAddress      IpAddress,
   gel2esw26kARPInspectionDynamicMACAddress     MacAddress
}

gel2esw26kARPInspectionDynamicIndex OBJECT-TYPE
   SYNTAX      INTEGER(1..4095)
   MAX-ACCESS  not-accessible
   STATUS      current
   DESCRIPTION
       " "
   ::= { gel2esw26kARPInspectionDynamicEntry 1 }

gel2esw26kARPInspectionDynamicPort OBJECT-TYPE
   SYNTAX      INTEGER(1..4095)
   MAX-ACCESS  read-only
   STATUS      current
   DESCRIPTION
       ""
   ::= { gel2esw26kARPInspectionDynamicEntry 2 }

gel2esw26kARPInspectionDynamicVLANId OBJECT-TYPE
   SYNTAX      INTEGER (1..4094)
   MAX-ACCESS  read-only
   STATUS      current
   DESCRIPTION
       ""
   ::= { gel2esw26kARPInspectionDynamicEntry 3 }

gel2esw26kARPInspectionDynamicIPAddress OBJECT-TYPE
   SYNTAX      IpAddress
   MAX-ACCESS  read-only
   STATUS      current
   DESCRIPTION
       ""
   ::= { gel2esw26kARPInspectionDynamicEntry 4 }

gel2esw26kARPInspectionDynamicMACAddress OBJECT-TYPE
   SYNTAX      MacAddress
   MAX-ACCESS  read-only
   STATUS      current
   DESCRIPTION
       ""
   ::= { gel2esw26kARPInspectionDynamicEntry 5 }

gel2esw26kDHCPSnooping                                          OBJECT IDENTIFIER ::= { gel2esw26kSecurity 3 }

gel2esw26kDHCPSnoopingConf                                          OBJECT IDENTIFIER ::= { gel2esw26kDHCPSnooping 1 }

gel2esw26kDHCPSnoopingMode OBJECT-TYPE
   SYNTAX      INTEGER(0|1)
   MAX-ACCESS  read-write
   STATUS      current
   DESCRIPTION
       "default: 0
       0: disable
       1: enable"
   ::= { gel2esw26kDHCPSnoopingConf 1 }

gel2esw26kDHCPSnoopingPortModeConfigurationTable OBJECT-TYPE
   SYNTAX      SEQUENCE OF GEL2ESW26KDHCPSnoopingPortModeConfigurationEntry
   MAX-ACCESS  not-accessible
   STATUS      current
   DESCRIPTION
       " "
   ::= { gel2esw26kDHCPSnoopingConf 2 }

gel2esw26kDHCPSnoopingPortModeConfigurationEntry OBJECT-TYPE
   SYNTAX      GEL2ESW26KDHCPSnoopingPortModeConfigurationEntry
   MAX-ACCESS  not-accessible
   STATUS      current
   DESCRIPTION
       ""
   INDEX    { gel2esw26kDHCPSnoopingPortModeConfigurationPort  }
   ::= { gel2esw26kDHCPSnoopingPortModeConfigurationTable 1 }

GEL2ESW26KDHCPSnoopingPortModeConfigurationEntry ::= SEQUENCE {
   gel2esw26kDHCPSnoopingPortModeConfigurationPort	INTEGER,
   gel2esw26kDHCPSnoopingPortModeConfigurationMode	INTEGER
}

gel2esw26kDHCPSnoopingPortModeConfigurationPort OBJECT-TYPE
   SYNTAX      INTEGER(1..4095)
   MAX-ACCESS  not-accessible
   STATUS      current
   DESCRIPTION
       " "
   ::= { gel2esw26kDHCPSnoopingPortModeConfigurationEntry 1 }

gel2esw26kDHCPSnoopingPortModeConfigurationMode OBJECT-TYPE
   SYNTAX      INTEGER (0|1)
   MAX-ACCESS  read-write
   STATUS      current
   DESCRIPTION
       "default: 1
       0: trust port mode
       1: untrust port mode"
   ::= { gel2esw26kDHCPSnoopingPortModeConfigurationEntry 2 }

gel2esw26kDHCPSnoopingStatisticsTable OBJECT-TYPE
   SYNTAX      SEQUENCE OF GEL2ESW26KDHCPSnoopingStatisticsEntry
   MAX-ACCESS  not-accessible
   STATUS      current
   DESCRIPTION
       " "
   ::= { gel2esw26kDHCPSnooping 2 }

gel2esw26kDHCPSnoopingStatisticsEntry OBJECT-TYPE
   SYNTAX      GEL2ESW26KDHCPSnoopingStatisticsEntry
   MAX-ACCESS  not-accessible
   STATUS      current
   DESCRIPTION
       ""
   INDEX    { gel2esw26kDHCPSnoopingStatisticsPort  }
   ::= { gel2esw26kDHCPSnoopingStatisticsTable 1 }

GEL2ESW26KDHCPSnoopingStatisticsEntry ::= SEQUENCE {
   gel2esw26kDHCPSnoopingStatisticsPort         INTEGER,
   gel2esw26kDHCPSnoopingStatisticsClear        INTEGER,
   gel2esw26kDHCPSnoopingRxDiscover             Counter32,
   gel2esw26kDHCPSnoopingRxOffer                Counter32,
   gel2esw26kDHCPSnoopingRxRequest              Counter32,
   gel2esw26kDHCPSnoopingRxDecline              Counter32,
   gel2esw26kDHCPSnoopingRxACK                  Counter32,
   gel2esw26kDHCPSnoopingRxNAK                  Counter32,
   gel2esw26kDHCPSnoopingRxRelease              Counter32,
   gel2esw26kDHCPSnoopingRxInform               Counter32,
   gel2esw26kDHCPSnoopingRxLeaseQuery           Counter32,
   gel2esw26kDHCPSnoopingRxLeaseUnassigned      Counter32,
   gel2esw26kDHCPSnoopingRxLeaseUnknown         Counter32,
   gel2esw26kDHCPSnoopingRxLeaseActive          Counter32,
   gel2esw26kDHCPSnoopingTxDiscover             Counter32,
   gel2esw26kDHCPSnoopingTxOffer                Counter32,
   gel2esw26kDHCPSnoopingTxRequest              Counter32,
   gel2esw26kDHCPSnoopingTxDecline              Counter32,
   gel2esw26kDHCPSnoopingTxACK                  Counter32,
   gel2esw26kDHCPSnoopingTxNAK                  Counter32,
   gel2esw26kDHCPSnoopingTxRelease              Counter32,
   gel2esw26kDHCPSnoopingTxInform               Counter32,
   gel2esw26kDHCPSnoopingTxLeaseQuery           Counter32,
   gel2esw26kDHCPSnoopingTxLeaseUnassigned      Counter32,
   gel2esw26kDHCPSnoopingTxLeaseUnknown         Counter32,
   gel2esw26kDHCPSnoopingTxLeaseActive          Counter32
}

gel2esw26kDHCPSnoopingStatisticsPort OBJECT-TYPE
   SYNTAX      INTEGER(1..4095)
   MAX-ACCESS  not-accessible
   STATUS      current
   DESCRIPTION
       " "
   ::= { gel2esw26kDHCPSnoopingStatisticsEntry 1 }

gel2esw26kDHCPSnoopingStatisticsClear OBJECT-TYPE
   SYNTAX      INTEGER (0|1)
   MAX-ACCESS  read-write
   STATUS      current
   DESCRIPTION
       "default: 0
       0: none
       1: clear"
   ::= { gel2esw26kDHCPSnoopingStatisticsEntry 2 }

gel2esw26kDHCPSnoopingRxDiscover OBJECT-TYPE
   SYNTAX      Counter32
   MAX-ACCESS  read-only
   STATUS      current
   DESCRIPTION
       " "
   ::= { gel2esw26kDHCPSnoopingStatisticsEntry 3 }

gel2esw26kDHCPSnoopingRxOffer OBJECT-TYPE
   SYNTAX      Counter32
   MAX-ACCESS  read-only
   STATUS      current
   DESCRIPTION
       " "
   ::= { gel2esw26kDHCPSnoopingStatisticsEntry 4 }

gel2esw26kDHCPSnoopingRxRequest OBJECT-TYPE
   SYNTAX      Counter32
   MAX-ACCESS  read-only
   STATUS      current
   DESCRIPTION
       " "
   ::= { gel2esw26kDHCPSnoopingStatisticsEntry 5 }

gel2esw26kDHCPSnoopingRxDecline OBJECT-TYPE
   SYNTAX      Counter32
   MAX-ACCESS  read-only
   STATUS      current
   DESCRIPTION
       " "
   ::= { gel2esw26kDHCPSnoopingStatisticsEntry 6 }

gel2esw26kDHCPSnoopingRxACK OBJECT-TYPE
   SYNTAX      Counter32
   MAX-ACCESS  read-only
   STATUS      current
   DESCRIPTION
       " "
   ::= { gel2esw26kDHCPSnoopingStatisticsEntry 7 }

gel2esw26kDHCPSnoopingRxNAK OBJECT-TYPE
   SYNTAX      Counter32
   MAX-ACCESS  read-only
   STATUS      current
   DESCRIPTION
       " "
   ::= { gel2esw26kDHCPSnoopingStatisticsEntry 8 }

gel2esw26kDHCPSnoopingRxRelease OBJECT-TYPE
   SYNTAX      Counter32
   MAX-ACCESS  read-only
   STATUS      current
   DESCRIPTION
       " "
   ::= { gel2esw26kDHCPSnoopingStatisticsEntry 9 }

gel2esw26kDHCPSnoopingRxInform OBJECT-TYPE
   SYNTAX      Counter32
   MAX-ACCESS  read-only
   STATUS      current
   DESCRIPTION
       " "
   ::= { gel2esw26kDHCPSnoopingStatisticsEntry 10 }

gel2esw26kDHCPSnoopingRxLeaseQuery OBJECT-TYPE
   SYNTAX      Counter32
   MAX-ACCESS  read-only
   STATUS      current
   DESCRIPTION
       " "
   ::= { gel2esw26kDHCPSnoopingStatisticsEntry 11 }

gel2esw26kDHCPSnoopingRxLeaseUnassigned OBJECT-TYPE
   SYNTAX      Counter32
   MAX-ACCESS  read-only
   STATUS      current
   DESCRIPTION
       " "
   ::= { gel2esw26kDHCPSnoopingStatisticsEntry 12 }

gel2esw26kDHCPSnoopingRxLeaseUnknown OBJECT-TYPE
   SYNTAX      Counter32
   MAX-ACCESS  read-only
   STATUS      current
   DESCRIPTION
       " "
   ::= { gel2esw26kDHCPSnoopingStatisticsEntry 13 }

gel2esw26kDHCPSnoopingRxLeaseActive OBJECT-TYPE
   SYNTAX      Counter32
   MAX-ACCESS  read-only
   STATUS      current
   DESCRIPTION
       " "
   ::= { gel2esw26kDHCPSnoopingStatisticsEntry 14 }

gel2esw26kDHCPSnoopingTxDiscover OBJECT-TYPE
   SYNTAX      Counter32
   MAX-ACCESS  read-only
   STATUS      current
   DESCRIPTION
       " "
   ::= { gel2esw26kDHCPSnoopingStatisticsEntry 15 }

gel2esw26kDHCPSnoopingTxOffer OBJECT-TYPE
   SYNTAX      Counter32
   MAX-ACCESS  read-only
   STATUS      current
   DESCRIPTION
       " "
   ::= { gel2esw26kDHCPSnoopingStatisticsEntry 16 }

gel2esw26kDHCPSnoopingTxRequest OBJECT-TYPE
   SYNTAX      Counter32
   MAX-ACCESS  read-only
   STATUS      current
   DESCRIPTION
       " "
   ::= { gel2esw26kDHCPSnoopingStatisticsEntry 17 }

gel2esw26kDHCPSnoopingTxDecline OBJECT-TYPE
   SYNTAX      Counter32
   MAX-ACCESS  read-only
   STATUS      current
   DESCRIPTION
       " "
   ::= { gel2esw26kDHCPSnoopingStatisticsEntry 18 }

gel2esw26kDHCPSnoopingTxACK OBJECT-TYPE
   SYNTAX      Counter32
   MAX-ACCESS  read-only
   STATUS      current
   DESCRIPTION
       " "
   ::= { gel2esw26kDHCPSnoopingStatisticsEntry 19 }

gel2esw26kDHCPSnoopingTxNAK OBJECT-TYPE
   SYNTAX      Counter32
   MAX-ACCESS  read-only
   STATUS      current
   DESCRIPTION
       " "
   ::= { gel2esw26kDHCPSnoopingStatisticsEntry 20 }

gel2esw26kDHCPSnoopingTxRelease OBJECT-TYPE
   SYNTAX      Counter32
   MAX-ACCESS  read-only
   STATUS      current
   DESCRIPTION
       " "
   ::= { gel2esw26kDHCPSnoopingStatisticsEntry 21 }

gel2esw26kDHCPSnoopingTxInform OBJECT-TYPE
   SYNTAX      Counter32
   MAX-ACCESS  read-only
   STATUS      current
   DESCRIPTION
       " "
   ::= { gel2esw26kDHCPSnoopingStatisticsEntry 22 }

gel2esw26kDHCPSnoopingTxLeaseQuery OBJECT-TYPE
   SYNTAX      Counter32
   MAX-ACCESS  read-only
   STATUS      current
   DESCRIPTION
       " "
   ::= { gel2esw26kDHCPSnoopingStatisticsEntry 23 }

gel2esw26kDHCPSnoopingTxLeaseUnassigned OBJECT-TYPE
   SYNTAX      Counter32
   MAX-ACCESS  read-only
   STATUS      current
   DESCRIPTION
       " "
   ::= { gel2esw26kDHCPSnoopingStatisticsEntry 24 }

gel2esw26kDHCPSnoopingTxLeaseUnknown OBJECT-TYPE
   SYNTAX      Counter32
   MAX-ACCESS  read-only
   STATUS      current
   DESCRIPTION
       " "
   ::= { gel2esw26kDHCPSnoopingStatisticsEntry 25 }

gel2esw26kDHCPSnoopingTxLeaseActive OBJECT-TYPE
   SYNTAX      Counter32
   MAX-ACCESS  read-only
   STATUS      current
   DESCRIPTION
       " "
   ::= { gel2esw26kDHCPSnoopingStatisticsEntry 26 }


gel2esw26kDHCPRelay                                             OBJECT IDENTIFIER ::= { gel2esw26kSecurity 4 }

gel2esw26kDHCPRelayConfiguration                                         OBJECT IDENTIFIER ::= { gel2esw26kDHCPRelay 1 }

gel2esw26kDHCPRelayMode OBJECT-TYPE
   SYNTAX      INTEGER(0|1)
   MAX-ACCESS  read-write
   STATUS      current
   DESCRIPTION
       "default: 0
       0: disable
       1: enable
       We need at least one server"
   ::= { gel2esw26kDHCPRelayConfiguration 1 }

gel2esw26kDHCPRelayServer OBJECT-TYPE
   SYNTAX      IpAddress
   MAX-ACCESS  read-write
   STATUS      current
   DESCRIPTION
       " "
   ::= { gel2esw26kDHCPRelayConfiguration 2 }

gel2esw26kDHCPRelayInformationMode OBJECT-TYPE
   SYNTAX      INTEGER(0|1)
   MAX-ACCESS  read-write
   STATUS      current
   DESCRIPTION
       "default: 0
       0: disable
       1: enable "
   ::= { gel2esw26kDHCPRelayConfiguration 3 }

gel2esw26kDHCPRelayInformationPolicy OBJECT-TYPE
   SYNTAX      INTEGER(0..2)
   MAX-ACCESS  read-write
   STATUS      current
   DESCRIPTION
       "default: 0
       0: replace
       1: keep
       2: drop "
   ::= { gel2esw26kDHCPRelayConfiguration 4 }

gel2esw26kDHCPRelayStatistics                                   OBJECT IDENTIFIER ::= { gel2esw26kDHCPRelay 2 }

gel2esw26kDHCPRelayServerStatistics                                   OBJECT IDENTIFIER ::= { gel2esw26kDHCPRelayStatistics 1 }

gel2esw26kServerStatTransmitToServer OBJECT-TYPE
   SYNTAX      Counter32
   MAX-ACCESS  read-only
   STATUS      current
   DESCRIPTION
       " "
   ::= { gel2esw26kDHCPRelayServerStatistics 1 }

gel2esw26kServerStatTransmitError OBJECT-TYPE
   SYNTAX      Counter32
   MAX-ACCESS  read-only
   STATUS      current
   DESCRIPTION
       " "
   ::= { gel2esw26kDHCPRelayServerStatistics 2 }

gel2esw26kServerStatReceiveFromServer OBJECT-TYPE
   SYNTAX      Counter32
   MAX-ACCESS  read-only
   STATUS      current
   DESCRIPTION
       " "
   ::= { gel2esw26kDHCPRelayServerStatistics 3 }

gel2esw26kServerStatReceiveMissingAgentOption OBJECT-TYPE
   SYNTAX      Counter32
   MAX-ACCESS  read-only
   STATUS      current
   DESCRIPTION
       " "
   ::= { gel2esw26kDHCPRelayServerStatistics 4 }

gel2esw26kServerStatReceiveMissingCircuitID OBJECT-TYPE
   SYNTAX      Counter32
   MAX-ACCESS  read-only
   STATUS      current
   DESCRIPTION
       " "
   ::= { gel2esw26kDHCPRelayServerStatistics 5 }

gel2esw26kServerStatReceiveMissingRemoteID OBJECT-TYPE
   SYNTAX      Counter32
   MAX-ACCESS  read-only
   STATUS      current
   DESCRIPTION
       " "
   ::= { gel2esw26kDHCPRelayServerStatistics 6 }

gel2esw26kServerStatReceiveBadCircuitID OBJECT-TYPE
   SYNTAX      Counter32
   MAX-ACCESS  read-only
   STATUS      current
   DESCRIPTION
       " "
   ::= { gel2esw26kDHCPRelayServerStatistics 7 }

gel2esw26kServerStatReceiveBadRemoteID OBJECT-TYPE
   SYNTAX      Counter32
   MAX-ACCESS  read-only
   STATUS      current
   DESCRIPTION
       " "
   ::= { gel2esw26kDHCPRelayServerStatistics 8 }

gel2esw26kDHCPRelayClientStatistics                                   OBJECT IDENTIFIER ::= { gel2esw26kDHCPRelayStatistics 2 }

gel2esw26kClientStatTransmitToClient OBJECT-TYPE
   SYNTAX      Counter32
   MAX-ACCESS  read-only
   STATUS      current
   DESCRIPTION
       " "
   ::= { gel2esw26kDHCPRelayClientStatistics 1 }

gel2esw26kClientStatTransmitError OBJECT-TYPE
   SYNTAX      Counter32
   MAX-ACCESS  read-only
   STATUS      current
   DESCRIPTION
       " "
   ::= { gel2esw26kDHCPRelayClientStatistics 2 }

gel2esw26kClientStatReceivefromClient OBJECT-TYPE
   SYNTAX      Counter32
   MAX-ACCESS  read-only
   STATUS      current
   DESCRIPTION
       " "
   ::= { gel2esw26kDHCPRelayClientStatistics 3 }

gel2esw26kClientStatReceiveAgentOption OBJECT-TYPE
   SYNTAX      Counter32
   MAX-ACCESS  read-only
   STATUS      current
   DESCRIPTION
       " "
   ::= { gel2esw26kDHCPRelayClientStatistics 4 }

gel2esw26kClientStatReplaceAgentOption OBJECT-TYPE
   SYNTAX      Counter32
   MAX-ACCESS  read-only
   STATUS      current
   DESCRIPTION
       " "
   ::= { gel2esw26kDHCPRelayClientStatistics 5 }

gel2esw26kClientStatKeepAgentOption OBJECT-TYPE
   SYNTAX      Counter32
   MAX-ACCESS  read-only
   STATUS      current
   DESCRIPTION
       " "
   ::= { gel2esw26kDHCPRelayClientStatistics 6 }

gel2esw26kClientStatDropAgentOption OBJECT-TYPE
   SYNTAX      Counter32
   MAX-ACCESS  read-only
   STATUS      current
   DESCRIPTION
       " "
   ::= { gel2esw26kDHCPRelayClientStatistics 7 }

gel2esw26kPortSecurity                                          OBJECT IDENTIFIER ::= { gel2esw26kSecurity 5 }

gel2esw26kPortSecLimitCtrl                                      OBJECT IDENTIFIER ::= { gel2esw26kPortSecurity 1 }

gel2esw26kPortSecLimitCtrlSystemConf                                      OBJECT IDENTIFIER ::= { gel2esw26kPortSecLimitCtrl 1 }

gel2esw26kPortSecurityMode OBJECT-TYPE
   SYNTAX      INTEGER(0|1)
   MAX-ACCESS  read-write
   STATUS      current
   DESCRIPTION
       "default: 0
       0: disable
       1: enable "
   ::= { gel2esw26kPortSecLimitCtrlSystemConf 1 }

gel2esw26kPortSecurityAging OBJECT-TYPE
   SYNTAX      INTEGER(0|1)
   MAX-ACCESS  read-write
   STATUS      current
   DESCRIPTION
       "default: 0
       0: disable
       1: enable "
   ::= { gel2esw26kPortSecLimitCtrlSystemConf 2 }

gel2esw26kPortSecurityAgingPeriod OBJECT-TYPE
   SYNTAX      INTEGER(10..10000000)
   MAX-ACCESS  read-write
   STATUS      current
   DESCRIPTION
       "default: 3600, range: 10-10000000 "
   ::= { gel2esw26kPortSecLimitCtrlSystemConf 3 }

gel2esw26kPortSecLimitCtrlTable OBJECT-TYPE
   SYNTAX      SEQUENCE OF GEL2ESW26KPortSecLimitCtrlEntry
   MAX-ACCESS  not-accessible
   STATUS      current
   DESCRIPTION
       " "
   ::= { gel2esw26kPortSecLimitCtrl 2 }

gel2esw26kPortSecLimitCtrlEntry OBJECT-TYPE
   SYNTAX      GEL2ESW26KPortSecLimitCtrlEntry
   MAX-ACCESS  not-accessible
   STATUS      current
   DESCRIPTION
       ""
   INDEX    { gel2esw26kPortSecLimitCtrlPort  }
   ::= { gel2esw26kPortSecLimitCtrlTable 1 }

GEL2ESW26KPortSecLimitCtrlEntry ::= SEQUENCE {
   gel2esw26kPortSecLimitCtrlPort           INTEGER,
   gel2esw26kPortSecLimitCtrlPortMode       INTEGER,
   gel2esw26kPortSecLimitCtrlPortLimit      INTEGER,
   gel2esw26kPortSecLimitCtrlPortAction     INTEGER,
   gel2esw26kPortSecLimitCtrlPortState      DisplayString,
   gel2esw26kPortSecLimitCtrlPortReOpen     INTEGER
}

gel2esw26kPortSecLimitCtrlPort OBJECT-TYPE
   SYNTAX      INTEGER (1..4095)
   MAX-ACCESS  not-accessible
   STATUS      current
   DESCRIPTION
       " "
   ::= { gel2esw26kPortSecLimitCtrlEntry 1 }

gel2esw26kPortSecLimitCtrlPortMode OBJECT-TYPE
   SYNTAX      INTEGER (0|1)
   MAX-ACCESS  read-write
   STATUS      current
   DESCRIPTION
       "default: 0
       0: disable
       1: enable"
   ::= { gel2esw26kPortSecLimitCtrlEntry 2 }

gel2esw26kPortSecLimitCtrlPortLimit OBJECT-TYPE
   SYNTAX      INTEGER(1..1024)
   MAX-ACCESS  read-write
   STATUS      current
   DESCRIPTION
       "default: 4, range: 1-1024"
   ::= { gel2esw26kPortSecLimitCtrlEntry 3 }

gel2esw26kPortSecLimitCtrlPortAction OBJECT-TYPE
   SYNTAX      INTEGER(0..3)
   MAX-ACCESS  read-write
   STATUS      current
   DESCRIPTION
       "default: 0
       0: none
       1: trap
       2: shutdown
       3: trap&shutdown"
   ::= { gel2esw26kPortSecLimitCtrlEntry 4 }

gel2esw26kPortSecLimitCtrlPortState OBJECT-TYPE
   SYNTAX      DisplayString
   MAX-ACCESS  read-only
   STATUS      current
   DESCRIPTION
       ""
   ::= { gel2esw26kPortSecLimitCtrlEntry 5 }

gel2esw26kPortSecLimitCtrlPortReOpen OBJECT-TYPE
   SYNTAX      INTEGER (0|1)
   MAX-ACCESS  read-write
   STATUS      current
   DESCRIPTION
       "default: 0
       0: none
       1: reopen"
   ::= { gel2esw26kPortSecLimitCtrlEntry 6 }

gel2esw26kPortSecSwitchStatusTable OBJECT-TYPE
   SYNTAX      SEQUENCE OF GEL2ESW26KPortSecSwitchStatusEntry
   MAX-ACCESS  not-accessible
   STATUS      current
   DESCRIPTION
       " "
   ::= { gel2esw26kPortSecurity 2 }

gel2esw26kPortSecSwitchStatusEntry OBJECT-TYPE
   SYNTAX      GEL2ESW26KPortSecSwitchStatusEntry
   MAX-ACCESS  not-accessible
   STATUS      current
   DESCRIPTION
       ""
   INDEX    { gel2esw26kPortSecSwitchStatusPort  }
   ::= { gel2esw26kPortSecSwitchStatusTable 1 }

GEL2ESW26KPortSecSwitchStatusEntry ::= SEQUENCE {
   gel2esw26kPortSecSwitchStatusPort                INTEGER,
   gel2esw26kPortSecSwitchStatusUsers               DisplayString,
   gel2esw26kPortSecSwitchStatusState               DisplayString,
   gel2esw26kPortSecSwitchStatusMACCountCurrent     INTEGER,
   gel2esw26kPortSecSwitchStatusMACCountLimit       INTEGER
}

gel2esw26kPortSecSwitchStatusPort OBJECT-TYPE
   SYNTAX      INTEGER (1..4095)
   MAX-ACCESS  not-accessible
   STATUS      current
   DESCRIPTION
       " "
   ::= { gel2esw26kPortSecSwitchStatusEntry 1 }

gel2esw26kPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { gel2esw26kPortSecSwitchStatusEntry 2 }

gel2esw26kPortSecSwitchStatusState OBJECT-TYPE
   SYNTAX      DisplayString
   MAX-ACCESS  read-only
   STATUS      current
   DESCRIPTION
       " Shows the current state of the port : Disabled, Ready, Limit Reached, Shutdown. "
   ::= { gel2esw26kPortSecSwitchStatusEntry 3 }

gel2esw26kPortSecSwitchStatusMACCountCurrent OBJECT-TYPE
   SYNTAX      INTEGER (1..4095)
   MAX-ACCESS  read-only
   STATUS      current
   DESCRIPTION
       ""
   ::= { gel2esw26kPortSecSwitchStatusEntry 4 }

gel2esw26kPortSecSwitchStatusMACCountLimit OBJECT-TYPE
   SYNTAX      INTEGER(1..4095)
   MAX-ACCESS  read-only
   STATUS      current
   DESCRIPTION
       ""
   ::= { gel2esw26kPortSecSwitchStatusEntry 5 }

gel2esw26kPortSecPortStatus                                      OBJECT IDENTIFIER ::= { gel2esw26kPortSecurity 3 }

gel2esw26kPortSecPortStatusPort OBJECT-TYPE
   SYNTAX       INTEGER (1..4095)
   MAX-ACCESS   read-write
   STATUS       current
   DESCRIPTION
       "port number
        default: 1
        range: 1 - port number."
   ::= { gel2esw26kPortSecPortStatus 1 }

gel2esw26kPortSecPortStatusTable OBJECT-TYPE
   SYNTAX      SEQUENCE OF GEL2ESW26KPortSecPortStatusEntry
   MAX-ACCESS  not-accessible
   STATUS      current
   DESCRIPTION
      " "
   ::= { gel2esw26kPortSecPortStatus 2 }

gel2esw26kPortSecPortStatusEntry OBJECT-TYPE
   SYNTAX      GEL2ESW26KPortSecPortStatusEntry
   MAX-ACCESS  not-accessible
   STATUS      current
   DESCRIPTION
       ""
   INDEX    { gel2esw26kPortSecPortStatusIndex  }
   ::= { gel2esw26kPortSecPortStatusTable 1 }

GEL2ESW26KPortSecPortStatusEntry ::= SEQUENCE {
   gel2esw26kPortSecPortStatusIndex              INTEGER,
   gel2esw26kPortSecPortStatusMACAddress         MacAddress,
   gel2esw26kPortSecPortStatusVLANId             INTEGER,
   gel2esw26kPortSecPortStatusState              DisplayString,
   gel2esw26kPortSecPortStatusTimeOfAddition     DisplayString,
   gel2esw26kPortSecPortStatusAgeAndHold         DisplayString
}

gel2esw26kPortSecPortStatusIndex OBJECT-TYPE
   SYNTAX      INTEGER(1..4095)
   MAX-ACCESS  not-accessible
   STATUS      current
   DESCRIPTION
       " "
   ::= { gel2esw26kPortSecPortStatusEntry 1 }

gel2esw26kPortSecPortStatusMACAddress OBJECT-TYPE
   SYNTAX      MacAddress
   MAX-ACCESS  read-only
   STATUS      current
   DESCRIPTION
       " "
   ::= { gel2esw26kPortSecPortStatusEntry 2 }

gel2esw26kPortSecPortStatusVLANId OBJECT-TYPE
   SYNTAX      INTEGER(1..4094)
   MAX-ACCESS  read-only
   STATUS      current
   DESCRIPTION
       " "
   ::= { gel2esw26kPortSecPortStatusEntry 3 }

gel2esw26kPortSecPortStatusState OBJECT-TYPE
   SYNTAX      DisplayString
   MAX-ACCESS  read-only
   STATUS      current
   DESCRIPTION
       "Blocked / Forwarding "
   ::= { gel2esw26kPortSecPortStatusEntry 4 }

gel2esw26kPortSecPortStatusTimeOfAddition OBJECT-TYPE
   SYNTAX      DisplayString
   MAX-ACCESS  read-only
   STATUS      current
   DESCRIPTION
       " "
   ::= { gel2esw26kPortSecPortStatusEntry 5 }

gel2esw26kPortSecPortStatusAgeAndHold OBJECT-TYPE
   SYNTAX      DisplayString
   MAX-ACCESS  read-only
   STATUS      current
   DESCRIPTION
       " "
   ::= { gel2esw26kPortSecPortStatusEntry 6 }


gel2esw26kAccessManagement                                      OBJECT IDENTIFIER ::= { gel2esw26kSecurity 6 }

gel2esw26kAccessMgtConf                                         OBJECT IDENTIFIER ::= { gel2esw26kAccessManagement 1 }

gel2esw26kAccessMgtConfMode OBJECT-TYPE
   SYNTAX      INTEGER(0|1)
   MAX-ACCESS  read-write
   STATUS      current
   DESCRIPTION
       "default: 0
       0: disable
       1: enable "
   ::= { gel2esw26kAccessMgtConf 1 }

gel2esw26kAccessMgtConfCreate OBJECT-TYPE
   SYNTAX      INTEGER(0|1)
   MAX-ACCESS  read-write
   STATUS      current
   DESCRIPTION
       "default: 0
       0: none
       1: create "
   ::= { gel2esw26kAccessMgtConf 2 }

gel2esw26kAccessMgtConfTable OBJECT-TYPE
   SYNTAX      SEQUENCE OF GEL2ESW26KAccessMgtConfEntry
   MAX-ACCESS  not-accessible
   STATUS      current
   DESCRIPTION
       " "
   ::= { gel2esw26kAccessMgtConf 3 }

gel2esw26kAccessMgtConfEntry OBJECT-TYPE
   SYNTAX      GEL2ESW26KAccessMgtConfEntry
   MAX-ACCESS  not-accessible
   STATUS      current
   DESCRIPTION
       ""
   INDEX    { gel2esw26kAccessMgtIndex  }
   ::= { gel2esw26kAccessMgtConfTable 1 }

GEL2ESW26KAccessMgtConfEntry ::= SEQUENCE {
   gel2esw26kAccessMgtIndex             INTEGER,
   gel2esw26kAccessMgtAddresstype       INTEGER,
   gel2esw26kAccessMgtStartIpAddress    DisplayString,
   gel2esw26kAccessMgtEndIpAddress      DisplayString,
   gel2esw26kAccessMgtHttpHttps         INTEGER,
   gel2esw26kAccessMgtSNMP              INTEGER,
   gel2esw26kAccessMgtTelnetSSH         INTEGER,
   gel2esw26kAccessMgtRowStatus         INTEGER
}

gel2esw26kAccessMgtIndex OBJECT-TYPE
   SYNTAX      INTEGER(1..16)
   MAX-ACCESS  read-write
   STATUS      current
   DESCRIPTION
       "Set Access Management config index
        range : 1-16."
   ::= { gel2esw26kAccessMgtConfEntry 1 }

gel2esw26kAccessMgtAddresstype OBJECT-TYPE
   SYNTAX      INTEGER(0|1)
   MAX-ACCESS  read-write
   STATUS      current
   DESCRIPTION
       "0: ipv4
        1: ipv6 "
   ::= { gel2esw26kAccessMgtConfEntry 2 }

gel2esw26kAccessMgtStartIpAddress OBJECT-TYPE
   SYNTAX      DisplayString
   MAX-ACCESS  read-write
   STATUS      current
   DESCRIPTION
       " Start IP address.
         IP address doesn't allowed all zero or all 'ff'H."
   ::= { gel2esw26kAccessMgtConfEntry 3 }

gel2esw26kAccessMgtEndIpAddress OBJECT-TYPE
   SYNTAX      DisplayString
   MAX-ACCESS  read-write
   STATUS      current
   DESCRIPTION
       " End IP address.
         IP address doesn't allowed all zero or all 'ff'H.
         End ip address is not less than start ip address."
   ::= { gel2esw26kAccessMgtConfEntry 4 }

gel2esw26kAccessMgtHttpHttps OBJECT-TYPE
   SYNTAX      INTEGER(0|1)
   MAX-ACCESS  read-write
   STATUS      current
   DESCRIPTION
       "default: 0
       0: disable
       1: enable "
   ::= { gel2esw26kAccessMgtConfEntry 5 }

gel2esw26kAccessMgtSNMP OBJECT-TYPE
   SYNTAX      INTEGER(0|1)
   MAX-ACCESS  read-write
   STATUS      current
   DESCRIPTION
       "default: 0
       0: disable
       1: enable "
   ::= { gel2esw26kAccessMgtConfEntry 6 }

gel2esw26kAccessMgtTelnetSSH OBJECT-TYPE
   SYNTAX      INTEGER(0|1)
   MAX-ACCESS  read-write
   STATUS      current
   DESCRIPTION
       "default: 0
       0: disable
       1: enable "
   ::= { gel2esw26kAccessMgtConfEntry 7 }

gel2esw26kAccessMgtRowStatus OBJECT-TYPE
   SYNTAX      INTEGER(1..5)
   MAX-ACCESS  read-write
   STATUS      current
   DESCRIPTION
       "1: active
        2: notInservice
        3: edit
        4: destroy
        5: undo"
   ::= { gel2esw26kAccessMgtConfEntry 8 }

gel2esw26kAccessMgtStatistics                                   OBJECT IDENTIFIER ::= { gel2esw26kAccessManagement 2 }

gel2esw26kHttpReceivedPkts OBJECT-TYPE
   SYNTAX      Counter32
   MAX-ACCESS  read-only
   STATUS      current
   DESCRIPTION
       " "
   ::= { gel2esw26kAccessMgtStatistics 1 }

gel2esw26kHttpAllowedPkts OBJECT-TYPE
   SYNTAX      Counter32
   MAX-ACCESS  read-only
   STATUS      current
   DESCRIPTION
       " "
   ::= { gel2esw26kAccessMgtStatistics 2 }

gel2esw26kHttpDiscardedPkts OBJECT-TYPE
   SYNTAX      Counter32
   MAX-ACCESS  read-only
   STATUS      current
   DESCRIPTION
       " "
   ::= { gel2esw26kAccessMgtStatistics 3 }

gel2esw26kHttpsReceivedPkts OBJECT-TYPE
   SYNTAX      Counter32
   MAX-ACCESS  read-only
   STATUS      current
   DESCRIPTION
       " "
   ::= { gel2esw26kAccessMgtStatistics 4 }

gel2esw26kHttpsAllowedPkts OBJECT-TYPE
   SYNTAX      Counter32
   MAX-ACCESS  read-only
   STATUS      current
   DESCRIPTION
       " "
   ::= { gel2esw26kAccessMgtStatistics 5 }

gel2esw26kHttpsDiscardedPkts OBJECT-TYPE
   SYNTAX      Counter32
   MAX-ACCESS  read-only
   STATUS      current
   DESCRIPTION
       " "
   ::= { gel2esw26kAccessMgtStatistics 6 }

gel2esw26kSnmpReceivedPkts OBJECT-TYPE
   SYNTAX      Counter32
   MAX-ACCESS  read-only
   STATUS      current
   DESCRIPTION
       " "
   ::= { gel2esw26kAccessMgtStatistics 7 }

gel2esw26kSnmpAllowedPkts OBJECT-TYPE
   SYNTAX      Counter32
   MAX-ACCESS  read-only
   STATUS      current
   DESCRIPTION
       " "
   ::= { gel2esw26kAccessMgtStatistics 8 }

gel2esw26kSnmpDiscardedPkts OBJECT-TYPE
   SYNTAX      Counter32
   MAX-ACCESS  read-only
   STATUS      current
   DESCRIPTION
       " "
   ::= { gel2esw26kAccessMgtStatistics 9 }

gel2esw26kTelnetReceivedPkts OBJECT-TYPE
   SYNTAX      Counter32
   MAX-ACCESS  read-only
   STATUS      current
   DESCRIPTION
       " "
   ::= { gel2esw26kAccessMgtStatistics 10 }

gel2esw26kTelnetAllowedPkts OBJECT-TYPE
   SYNTAX      Counter32
   MAX-ACCESS  read-only
   STATUS      current
   DESCRIPTION
       " "
   ::= { gel2esw26kAccessMgtStatistics 11 }

gel2esw26kTelnetDiscardedPkts OBJECT-TYPE
   SYNTAX      Counter32
   MAX-ACCESS  read-only
   STATUS      current
   DESCRIPTION
       " "
   ::= { gel2esw26kAccessMgtStatistics 12 }

gel2esw26kSSHReceivedPkts OBJECT-TYPE
   SYNTAX      Counter32
   MAX-ACCESS  read-only
   STATUS      current
   DESCRIPTION
       " "
   ::= { gel2esw26kAccessMgtStatistics 13 }

gel2esw26kSSHAllowedPkts OBJECT-TYPE
   SYNTAX      Counter32
   MAX-ACCESS  read-only
   STATUS      current
   DESCRIPTION
       " "
   ::= { gel2esw26kAccessMgtStatistics 14 }

gel2esw26kSSHDiscardedPkts OBJECT-TYPE
   SYNTAX      Counter32
   MAX-ACCESS  read-only
   STATUS      current
   DESCRIPTION
       " "
   ::= { gel2esw26kAccessMgtStatistics 15 }

gel2esw26kAccessMgtStatisticsClearAll OBJECT-TYPE
   SYNTAX      INTEGER(0|1)
   MAX-ACCESS  read-write
   STATUS      current
   DESCRIPTION
       "0: none
        1: clear"
   ::= { gel2esw26kAccessMgtStatistics 16 }

gel2esw26kSSH                                                   OBJECT IDENTIFIER ::= { gel2esw26kSecurity 7 }

gel2esw26kSSHMode OBJECT-TYPE
   SYNTAX      INTEGER(0|1)
   MAX-ACCESS  read-write
   STATUS      current
   DESCRIPTION
       "default: 1
        0: disable
        1: enable"
   ::= { gel2esw26kSSH 1 }

gel2esw26kHTTPS                                                 OBJECT IDENTIFIER ::= { gel2esw26kSecurity 8 }

gel2esw26kHTTPSMode OBJECT-TYPE
   SYNTAX      INTEGER(0|1)
   MAX-ACCESS  read-write
   STATUS      current
   DESCRIPTION
       "default: 1
        0: disable
        1: enable"
   ::= { gel2esw26kHTTPS 1 }

gel2esw26kHTTPSAutoRedirect OBJECT-TYPE
   SYNTAX      INTEGER(0|1)
   MAX-ACCESS  read-write
   STATUS      current
   DESCRIPTION
       "default: 0
        0: disable
        1: enable"
   ::= { gel2esw26kHTTPS 2 }

gel2esw26kAuthMethod                                            OBJECT IDENTIFIER ::= { gel2esw26kSecurity 9 }

gel2esw26kConsoleAuthMethod OBJECT-TYPE
   SYNTAX      INTEGER(0..3)
   MAX-ACCESS  read-write
   STATUS      current
   DESCRIPTION
       "default: 1
        0: none
        1: local
        2: RADIUS
        3: TACACS+"
   ::= { gel2esw26kAuthMethod 1 }

gel2esw26kConsoleFallback OBJECT-TYPE
   SYNTAX      INTEGER(0|1)
   MAX-ACCESS  read-write
   STATUS      current
   DESCRIPTION
       "default: 0
        0:disable
        1:enable"
   ::= { gel2esw26kAuthMethod 2 }

gel2esw26kTelnetAuthMethod OBJECT-TYPE
   SYNTAX      INTEGER(0..3)
   MAX-ACCESS  read-write
   STATUS      current
   DESCRIPTION
       "default: 1
        0: none
        1: local
        2: RADIUS
        3: TACACS+"
   ::= { gel2esw26kAuthMethod 3 }

gel2esw26kTelnetFallback OBJECT-TYPE
   SYNTAX      INTEGER(0|1)
   MAX-ACCESS  read-write
   STATUS      current
   DESCRIPTION
       "default: 0
        0:disable
        1:enable"
   ::= { gel2esw26kAuthMethod 4 }

gel2esw26kSshAuthMethod OBJECT-TYPE
   SYNTAX      INTEGER(0..3)
   MAX-ACCESS  read-write
   STATUS      current
   DESCRIPTION
       "default: 1
        0: none
        1: local
        2: RADIUS
        3: TACACS+"
   ::= { gel2esw26kAuthMethod 5 }

gel2esw26kSshFallback OBJECT-TYPE
   SYNTAX      INTEGER(0|1)
   MAX-ACCESS  read-write
   STATUS      current
   DESCRIPTION
       "default: 0
        0:disable
        1:enable"
   ::= { gel2esw26kAuthMethod 6 }

gel2esw26kWebAuthMethod OBJECT-TYPE
   SYNTAX      INTEGER(0..3)
   MAX-ACCESS  read-write
   STATUS      current
   DESCRIPTION
       "default: 1
        0: none
        1: local
        2: RADIUS
        3: TACACS+"
   ::= { gel2esw26kAuthMethod 7 }

gel2esw26kWebFallback OBJECT-TYPE
   SYNTAX      INTEGER(0|1)
   MAX-ACCESS  read-write
   STATUS      current
   DESCRIPTION
       "default: 0
        0:disable
        1:enable"
   ::= { gel2esw26kAuthMethod 8 }

gel2esw26kMaintenance                                           OBJECT IDENTIFIER ::= { gel2esw26kProductId 4 }

gel2esw26kRestartDevice OBJECT-TYPE
   SYNTAX      INTEGER(0|1)
   MAX-ACCESS  read-write
   STATUS      current
   DESCRIPTION
       "default: 0
        0:none
        1:yes"
   ::= { gel2esw26kMaintenance 1 }

gel2esw26kFirmware                                         OBJECT IDENTIFIER ::= { gel2esw26kMaintenance 2 }

gel2esw26kFirmwareIpAddress OBJECT-TYPE
   SYNTAX       IpAddress
   MAX-ACCESS   read-write
   STATUS       current
   DESCRIPTION
        "Get/Set the firmware tftp server."
   ::= { gel2esw26kFirmware 1 }

gel2esw26kFirmwareFileName OBJECT-TYPE
   SYNTAX       DisplayString
   MAX-ACCESS   read-write
   STATUS       current
   DESCRIPTION
        "Get/Set the path and filename for firmware upgrading."
   ::= { gel2esw26kFirmware 2 }

gel2esw26kDoFirmwareUpgrade OBJECT-TYPE
   SYNTAX       INTEGER(0|1)
   MAX-ACCESS   read-write
   STATUS       current
   DESCRIPTION
        "Do firmware upgrade. Get this OID always return zero.
              1 - do firmware upgrade.
              0 - do nothing."
   ::= { gel2esw26kFirmware 3 }

gel2esw26kSaveOrRestore                                         OBJECT IDENTIFIER ::= { gel2esw26kMaintenance 3 }

gel2esw26kFactoryDefaults OBJECT-TYPE
   SYNTAX      INTEGER(0|1)
   MAX-ACCESS  read-write
   STATUS      current
   DESCRIPTION
       "default: 0
        0:none
        1:yes"
   ::= { gel2esw26kSaveOrRestore 1 }

gel2esw26kSaveStart OBJECT-TYPE
   SYNTAX      INTEGER(0|1)
   MAX-ACCESS  read-write
   STATUS      current
   DESCRIPTION
       "default: 0
        0:none
        1:yes"
   ::= { gel2esw26kSaveOrRestore 2 }

gel2esw26kSaveUser OBJECT-TYPE
   SYNTAX      INTEGER(0|1)
   MAX-ACCESS  read-write
   STATUS      current
   DESCRIPTION
       "default: 0
        0:none
        1:yes"
   ::= { gel2esw26kSaveOrRestore 3 }

gel2esw26kRestoreUser OBJECT-TYPE
   SYNTAX      INTEGER(0|1)
   MAX-ACCESS  read-write
   STATUS      current
   DESCRIPTION
       "default: 0
        0:none
        1:yes"
   ::= { gel2esw26kSaveOrRestore 4 }


gel2esw26kExportOrImport                                        OBJECT IDENTIFIER ::= { gel2esw26kMaintenance 4 }

gel2esw26kExportIpAddress OBJECT-TYPE
   SYNTAX       IpAddress
   MAX-ACCESS   read-write
   STATUS       current
   DESCRIPTION
        "Get/Set the export tftp server."
   ::= { gel2esw26kExportOrImport 1 }

gel2esw26kExportConfigName OBJECT-TYPE
   SYNTAX       DisplayString
   MAX-ACCESS   read-write
   STATUS       current
   DESCRIPTION
       "Get/Set the export file path and name."
   ::= { gel2esw26kExportOrImport 2 }

gel2esw26kDoExportConfig OBJECT-TYPE
   SYNTAX       INTEGER(1)
   MAX-ACCESS   read-write
   STATUS       current
   DESCRIPTION
        "Do export-config.
         Get this OID always return zero.
         1 - export."
   ::= { gel2esw26kExportOrImport 3 }

gel2esw26kImportIpAddress OBJECT-TYPE
   SYNTAX       IpAddress
   MAX-ACCESS   read-write
   STATUS       current
   DESCRIPTION
        "Get/Set the import tftp server."
   ::= { gel2esw26kExportOrImport 4 }

gel2esw26kImportConfigName OBJECT-TYPE
   SYNTAX      DisplayString
   MAX-ACCESS  read-write
   STATUS      current
   DESCRIPTION
       "Get/Set the import file path and name."
   ::= { gel2esw26kExportOrImport 5 }

gel2esw26kDoImportConfig OBJECT-TYPE
   SYNTAX       INTEGER(1)
   MAX-ACCESS   read-write
   STATUS       current
   DESCRIPTION
        "Do export-config.
         Get this OID always return zero.
         1 - import."
   ::= { gel2esw26kExportOrImport 6 }

gel2esw26kDiagnostics                                           OBJECT IDENTIFIER ::= { gel2esw26kMaintenance 5 }

gel2esw26kPingIpAddress OBJECT-TYPE
   SYNTAX      IpAddress
   MAX-ACCESS  read-write
   STATUS      current
   DESCRIPTION
       " The destination IP Address. "
   ::= { gel2esw26kDiagnostics 1 }

gel2esw26kPingSize OBJECT-TYPE
   SYNTAX      INTEGER(60..1400)
   MAX-ACCESS  read-write
   STATUS      current
   DESCRIPTION
       " Size of ICMP echo packet.
         range : 60-1400, default : 64. "
   ::= { gel2esw26kDiagnostics 2 }

gel2esw26kDoPingConfig OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gel2esw26kDiagnostics 3 }

gel2esw26kPingResult OBJECT-TYPE
   SYNTAX      DisplayString
   MAX-ACCESS  read-only
   STATUS      current
   DESCRIPTION
       " Show ping result. "
   ::= { gel2esw26kDiagnostics 4 }

gel2esw26kPing6IpAddress OBJECT-TYPE
   SYNTAX      DisplayString
   MAX-ACCESS  read-write
   STATUS      current
   DESCRIPTION
       " The destination IPv6 Address. "
   ::= { gel2esw26kDiagnostics 5 }

gel2esw26kPing6Size OBJECT-TYPE
   SYNTAX      INTEGER(60..1400)
   MAX-ACCESS  read-write
   STATUS      current
   DESCRIPTION
       " Size of ICMP echo packet.
         range : 60-1400. "
   ::= { gel2esw26kDiagnostics 6 }

gel2esw26kDoPing6Config OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gel2esw26kDiagnostics 7 }

gel2esw26kPing6Result OBJECT-TYPE
   SYNTAX      DisplayString
   MAX-ACCESS  read-only
   STATUS      current
   DESCRIPTION
       " Show ping result. "
   ::= { gel2esw26kDiagnostics 8 }


gel2esw26kVeriPHY                                           OBJECT IDENTIFIER ::= { gel2esw26kDiagnostics 9 }

gel2esw26kVeriPHYTest OBJECT-TYPE
   SYNTAX      INTEGER (1..4095)
   MAX-ACCESS  read-write
   STATUS      current
   DESCRIPTION
       "Run VeriPHY Cable Diagnostics.
        port, range : 0 - port number.
        0 : ALL "
   ::= { gel2esw26kVeriPHY 1 }

gel2esw26kVeriPHYTable OBJECT-TYPE
   SYNTAX      SEQUENCE OF GEL2ESW26KVeriPHYEntry
   MAX-ACCESS  not-accessible
   STATUS      current
   DESCRIPTION
       " "
   ::= { gel2esw26kVeriPHY 2 }

gel2esw26kVeriPHYEntry OBJECT-TYPE
   SYNTAX      GEL2ESW26KVeriPHYEntry
   MAX-ACCESS  not-accessible
   STATUS      current
   DESCRIPTION
       ""
   INDEX    { gel2esw26kVeriPHYPort  }
   ::= { gel2esw26kVeriPHYTable 1 }

GEL2ESW26KVeriPHYEntry ::= SEQUENCE {
   gel2esw26kVeriPHYPort        INTEGER,
   gel2esw26kVeriPHYPairA       DisplayString,
   gel2esw26kVeriPHYLengthA     DisplayString,
   gel2esw26kVeriPHYPairB       DisplayString,
   gel2esw26kVeriPHYLengthB     DisplayString,
   gel2esw26kVeriPHYPairC       DisplayString,
   gel2esw26kVeriPHYLengthC     DisplayString,
   gel2esw26kVeriPHYPairD       DisplayString,
   gel2esw26kVeriPHYLengthD     DisplayString
}

gel2esw26kVeriPHYPort OBJECT-TYPE
   SYNTAX      INTEGER (1..4095)
   MAX-ACCESS  not-accessible
   STATUS      current
   DESCRIPTION
       " The length (in meters) of the cable pair. "
   ::= { gel2esw26kVeriPHYEntry 1 }

gel2esw26kVeriPHYPairA OBJECT-TYPE
   SYNTAX      DisplayString
   MAX-ACCESS  read-only
   STATUS      current
   DESCRIPTION
       " The status of the cable pair. "
   ::= { gel2esw26kVeriPHYEntry 2 }

gel2esw26kVeriPHYLengthA OBJECT-TYPE
   SYNTAX      DisplayString
   MAX-ACCESS  read-only
   STATUS      current
   DESCRIPTION
       " The length (in meters) of the cable pair. "
   ::= { gel2esw26kVeriPHYEntry 3 }

gel2esw26kVeriPHYPairB OBJECT-TYPE
   SYNTAX      DisplayString
   MAX-ACCESS  read-only
   STATUS      current
   DESCRIPTION
       " The status of the cable pair. "
   ::= { gel2esw26kVeriPHYEntry 4 }

gel2esw26kVeriPHYLengthB OBJECT-TYPE
   SYNTAX      DisplayString
   MAX-ACCESS  read-only
   STATUS      current
   DESCRIPTION
       " The length (in meters) of the cable pair. "
   ::= { gel2esw26kVeriPHYEntry 5 }

gel2esw26kVeriPHYPairC OBJECT-TYPE
   SYNTAX      DisplayString
   MAX-ACCESS  read-only
   STATUS      current
   DESCRIPTION
       " The status of the cable pair. "
   ::= { gel2esw26kVeriPHYEntry 6 }

gel2esw26kVeriPHYLengthC OBJECT-TYPE
   SYNTAX      DisplayString
   MAX-ACCESS  read-only
   STATUS      current
   DESCRIPTION
       " The length (in meters) of the cable pair. "
   ::= { gel2esw26kVeriPHYEntry 7 }

gel2esw26kVeriPHYPairD OBJECT-TYPE
   SYNTAX      DisplayString
   MAX-ACCESS  read-only
   STATUS      current
   DESCRIPTION
       " The status of the cable pair. "
   ::= { gel2esw26kVeriPHYEntry 8 }

gel2esw26kVeriPHYLengthD OBJECT-TYPE
   SYNTAX      DisplayString
   MAX-ACCESS  read-only
   STATUS      current
   DESCRIPTION
       " The length (in meters) of the cable pair. "
   ::= { gel2esw26kVeriPHYEntry 9 }


------------------------------------------------------------------------------------------------------------------
gel2esw26kTrap                                                  OBJECT IDENTIFIER ::= { gel2esw26kProductId 5 }

gel2esw26kTrapEvent                                             OBJECT IDENTIFIER ::= { gel2esw26kTrap 1 }

gel2esw26kEmergency NOTIFICATION-TYPE
  OBJECTS   { gel2esw26kInformation }
  STATUS        current
    DESCRIPTION
        "The severity level is Emergency. The system is unusable."
    ::= { gel2esw26kTrapEvent 1 }

gel2esw26kAlert NOTIFICATION-TYPE
  OBJECTS   { gel2esw26kInformation }
  STATUS        current
    DESCRIPTION
        "The severity level is Alert. The action must be taken immediately."
    ::= { gel2esw26kTrapEvent 2 }

gel2esw26kCritical NOTIFICATION-TYPE
  OBJECTS   { gel2esw26kInformation }
  STATUS        current
    DESCRIPTION
        "The severity level is Critical. Critical conditions."
    ::= { gel2esw26kTrapEvent 3 }

gel2esw26kError NOTIFICATION-TYPE
  OBJECTS   { gel2esw26kInformation }
  STATUS        current
    DESCRIPTION
        "The severity level is Error. Error conditions."
    ::= { gel2esw26kTrapEvent 4 }

gel2esw26kWarning NOTIFICATION-TYPE
  OBJECTS   { gel2esw26kInformation }
  STATUS        current
    DESCRIPTION
        "The severity level is Warning. Warning conditions."
    ::= { gel2esw26kTrapEvent 5 }

gel2esw26kNotice NOTIFICATION-TYPE
  OBJECTS   { gel2esw26kInformation }
  STATUS        current
    DESCRIPTION
        "The severity level is Notice. Normal but significant condition."
    ::= { gel2esw26kTrapEvent 6 }

gel2esw26kInformational NOTIFICATION-TYPE
  OBJECTS   { gel2esw26kInformation }
  STATUS        current
    DESCRIPTION
        "The severity level is Informational. Informational messages."
    ::= { gel2esw26kTrapEvent 7 }

gel2esw26kDebug NOTIFICATION-TYPE
  OBJECTS   { gel2esw26kInformation }
  STATUS        current
    DESCRIPTION
        "The severity level is Debug. debug-level messages."
    ::= { gel2esw26kTrapEvent 8 }

gel2esw26kTrapVariable                                          OBJECT IDENTIFIER ::= { gel2esw26kTrap 2 }

gel2esw26kInformation OBJECT-TYPE
    SYNTAX      DisplayString
    MAX-ACCESS  read-only
    STATUS      current
    DESCRIPTION
        "Trap information."
    ::= { gel2esw26kTrapVariable 1 }


END
