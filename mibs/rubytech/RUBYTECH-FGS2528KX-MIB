RUBYTECH-FGS2528KX-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

rubytech MODULE-IDENTITY
        LAST-UPDATED "201205150000Z"
        ORGANIZATION "Corp."
        CONTACT-INFO
            ""
        DESCRIPTION
            ""
        ::= { enterprises 5205 }

switch                                                          OBJECT IDENTIFIER ::= { rubytech 2 }

fgs2528kxProductId                                             OBJECT IDENTIFIER ::= { switch 77 }

fgs2528kxSystem                                                OBJECT IDENTIFIER ::= { fgs2528kxProductId 1 }

fgs2528kxSystemInformation                                     OBJECT IDENTIFIER ::= { fgs2528kxSystem 1 }

fgs2528kxModelName OBJECT-TYPE
   SYNTAX       DisplayString
   MAX-ACCESS   read-only
   STATUS       current
   DESCRIPTION
       ""
 ::= { fgs2528kxSystemInformation 1 }

fgs2528kxBIOSVersion OBJECT-TYPE
   SYNTAX       DisplayString
   MAX-ACCESS   read-only
   STATUS       current
   DESCRIPTION
       ""
   ::= { fgs2528kxSystemInformation 2 }

fgs2528kxFirmwareVersion OBJECT-TYPE
   SYNTAX       DisplayString
   MAX-ACCESS   read-only
   STATUS       current
   DESCRIPTION
       ""
   ::= { fgs2528kxSystemInformation 3 }

fgs2528kxHardwareMechanicalVersion OBJECT-TYPE
   SYNTAX       DisplayString
   MAX-ACCESS   read-only
   STATUS       current
   DESCRIPTION
       ""
   ::= { fgs2528kxSystemInformation 4 }

fgs2528kxSeriesNumber OBJECT-TYPE
   SYNTAX       DisplayString
   MAX-ACCESS   read-only
   STATUS       current
   DESCRIPTION
       ""
   ::= { fgs2528kxSystemInformation 5 }

fgs2528kxHostMACAddress OBJECT-TYPE
   SYNTAX       MacAddress
   MAX-ACCESS   read-only
   STATUS       current
   DESCRIPTION
       ""
   ::= { fgs2528kxSystemInformation 6 }

fgs2528kxConsoleBaudrate OBJECT-TYPE
   SYNTAX       DisplayString
   MAX-ACCESS   read-only
   STATUS       current
   DESCRIPTION
       ""
   ::= { fgs2528kxSystemInformation 7 }

fgs2528kxRAMSize OBJECT-TYPE
   SYNTAX       DisplayString
   MAX-ACCESS   read-only
   STATUS       current
   DESCRIPTION
       ""
   ::= { fgs2528kxSystemInformation 8 }

fgs2528kxFlashSize OBJECT-TYPE
   SYNTAX       DisplayString
   MAX-ACCESS   read-only
   STATUS       current
   DESCRIPTION
       ""
   ::= { fgs2528kxSystemInformation 9 }

fgs2528kxBridgeFBDSize OBJECT-TYPE
   SYNTAX       DisplayString
   MAX-ACCESS   read-only
   STATUS       current
   DESCRIPTION
       ""
   ::= { fgs2528kxSystemInformation 10 }

fgs2528kxTransmitQueue OBJECT-TYPE
   SYNTAX       DisplayString
   MAX-ACCESS   read-only
   STATUS       current
   DESCRIPTION
       ""
   ::= { fgs2528kxSystemInformation 11 }

fgs2528kxMaximumFrameSize OBJECT-TYPE
   SYNTAX       DisplayString
   MAX-ACCESS   read-only
   STATUS       current
   DESCRIPTION
       ""
   ::= { fgs2528kxSystemInformation 12 }

fgs2528kxCPULoad OBJECT-TYPE
   SYNTAX       DisplayString
   MAX-ACCESS   read-only
   STATUS       current
   DESCRIPTION
       ""
   ::= { fgs2528kxSystemInformation 13 }

fgs2528kxFanSpeed OBJECT-TYPE
   SYNTAX       DisplayString
   MAX-ACCESS   read-only
   STATUS       current
   DESCRIPTION
       ""
   ::= { fgs2528kxSystemInformation 14 }

fgs2528kxPowers OBJECT-TYPE
   SYNTAX       DisplayString
   MAX-ACCESS   read-only
   STATUS       current
   DESCRIPTION
       ""
   ::= { fgs2528kxSystemInformation 15 }

fgs2528kxTemperature1 OBJECT-TYPE
   SYNTAX       DisplayString
   MAX-ACCESS   read-only
   STATUS       current
   DESCRIPTION
       ""
   ::= { fgs2528kxSystemInformation 16 }

fgs2528kxTemperature2 OBJECT-TYPE
   SYNTAX       DisplayString
   MAX-ACCESS   read-only
   STATUS       current
   DESCRIPTION
       ""
   ::= { fgs2528kxSystemInformation 17 }

fgs2528kxTemperature3 OBJECT-TYPE
   SYNTAX       DisplayString
   MAX-ACCESS   read-only
   STATUS       current
   DESCRIPTION
       ""
   ::= { fgs2528kxSystemInformation 18 }

fgs2528kxTemperature4 OBJECT-TYPE
   SYNTAX       DisplayString
   MAX-ACCESS   read-only
   STATUS       current
   DESCRIPTION
       ""
   ::= { fgs2528kxSystemInformation 19 }


fgs2528kxSystemTime                                            OBJECT IDENTIFIER ::= { fgs2528kxSystem 2 }

fgs2528kxSystemTimeManual                                      OBJECT IDENTIFIER ::= { fgs2528kxSystemTime 1 }

fgs2528kxSystemTimeManualClockSource OBJECT-TYPE
   SYNTAX       INTEGER(0|1)
   MAX-ACCESS   read-write
   STATUS       current
   DESCRIPTION
       "default: 0,
        0 : Use Local Settings,
        1 : Use NTP Server."
   ::= { fgs2528kxSystemTimeManual 1 }

fgs2528kxSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { fgs2528kxSystemTimeManual 2 }

fgs2528kxSystemTimeManualTimeZoneOffset OBJECT-TYPE
   SYNTAX       INTEGER(-720..780)
   MAX-ACCESS   read-write
   STATUS       current
   DESCRIPTION
       "Get/Set the NTP Time Zone.
        The value range is between -720 and 780 (minutes)."
   ::= { fgs2528kxSystemTimeManual 3 }

fgs2528kxSystemTimeManualDaylightSavings OBJECT-TYPE
   SYNTAX       INTEGER(0|1)
   MAX-ACCESS   read-write
   STATUS       current
   DESCRIPTION
       "default: 0,
        0 : Disable,
        1 : Enable."
   ::= { fgs2528kxSystemTimeManual 4 }

fgs2528kxSystemTimeManualTimeSetOffset OBJECT-TYPE
   SYNTAX       INTEGER(1..1440)
   MAX-ACCESS   read-write
   STATUS       current
   DESCRIPTION
       "Get/Set the Daylight Saving Time.
        The value range is between 1 and 1440 (minutes),
        Default : 60 (minutes)."
   ::= { fgs2528kxSystemTimeManual 5 }

fgs2528kxSystemTimeManualDaylightSavingsType OBJECT-TYPE
   SYNTAX       INTEGER(0|1)
   MAX-ACCESS   read-write
   STATUS       current
   DESCRIPTION
       "default: 0,
        0 : By dates,
        1 : Recurring."
   ::= { fgs2528kxSystemTimeManual 6 }

fgs2528kxSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { fgs2528kxSystemTimeManual 7 }

fgs2528kxSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { fgs2528kxSystemTimeManual 8 }

fgs2528kxSystemTimeManualDaylightSavingsRecurringDayFrom OBJECT-TYPE
   SYNTAX       INTEGER(0..6)
   MAX-ACCESS   read-write
   STATUS       current
   DESCRIPTION
       "Get/Set the Daylight Saving Time Day From.
        0 : Sun, 1 : Mon, 2 : Tue, 3 : Wed, 4 : Thu, 5 : Fri, 6 : Sat."
   ::= { fgs2528kxSystemTimeManual 9 }

fgs2528kxSystemTimeManualDaylightSavingsRecurringWeekFrom OBJECT-TYPE
   SYNTAX       INTEGER(1..5)
   MAX-ACCESS   read-write
   STATUS       current
   DESCRIPTION
       "Get/Set the Daylight Saving Time Week From.
        1 : first week, 2, 3, 4, 5 : last week"
   ::= { fgs2528kxSystemTimeManual 10 }

fgs2528kxSystemTimeManualDaylightSavingsRecurringMonthFrom OBJECT-TYPE
   SYNTAX       INTEGER(0..11)
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { fgs2528kxSystemTimeManual 11 }

fgs2528kxSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { fgs2528kxSystemTimeManual 12 }

fgs2528kxSystemTimeManualDaylightSavingsRecurringDayTo OBJECT-TYPE
   SYNTAX       INTEGER(0..6)
   MAX-ACCESS   read-write
   STATUS       current
   DESCRIPTION
       "Get/Set the Daylight Saving Time Day To.
        0 : Sun, 1 : Mon, 2 : Tue, 3 : Wed, 4 : Thu, 5 : Fri, 6 : Sat."
   ::= { fgs2528kxSystemTimeManual 13 }

fgs2528kxSystemTimeManualDaylightSavingsRecurringWeekTo OBJECT-TYPE
   SYNTAX       INTEGER(1..5)
   MAX-ACCESS   read-write
   STATUS       current
   DESCRIPTION
       "Get/Set the Daylight Saving Time Week To.
        1 : first week, 2, 3, 4, 5 : last week"
   ::= { fgs2528kxSystemTimeManual 14 }

fgs2528kxSystemTimeManualDaylightSavingsRecurringMonthTo OBJECT-TYPE
   SYNTAX       INTEGER(0..11)
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { fgs2528kxSystemTimeManual 15 }

fgs2528kxSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { fgs2528kxSystemTimeManual 16 }

fgs2528kxSystemTimeNTP                                     OBJECT IDENTIFIER ::= { fgs2528kxSystemTime 2 }

fgs2528kxSystemTimeNTPTable OBJECT-TYPE
   SYNTAX      SEQUENCE OF FGS2528KXSystemTimeNTPEntry
   MAX-ACCESS  not-accessible
   STATUS      current
   DESCRIPTION
       " "
   ::= { fgs2528kxSystemTimeNTP 1 }

fgs2528kxSystemTimeNTPEntry OBJECT-TYPE
   SYNTAX      FGS2528KXSystemTimeNTPEntry
   MAX-ACCESS  not-accessible
   STATUS      current
   DESCRIPTION
       ""
   INDEX    { fgs2528kxSystemTimeNTPIndex  }
   ::= { fgs2528kxSystemTimeNTPTable 1 }

FGS2528KXSystemTimeNTPEntry ::= SEQUENCE {
   fgs2528kxSystemTimeNTPIndex             INTEGER,
   fgs2528kxSystemTimeNTPServerIPType      INTEGER,
   fgs2528kxSystemTimeNTPServer            DisplayString,
   fgs2528kxSystemTimeNTPCurrentMode       INTEGER
}

fgs2528kxSystemTimeNTPIndex OBJECT-TYPE
   SYNTAX      INTEGER (1..5)
   MAX-ACCESS  not-accessible
   STATUS      current
   DESCRIPTION
       " The index of the ntp entry. "
   ::= { fgs2528kxSystemTimeNTPEntry 1 }

fgs2528kxSystemTimeNTPServerIPType OBJECT-TYPE
   SYNTAX       INTEGER(0|1)
   MAX-ACCESS   read-write
   STATUS       current
   DESCRIPTION
       "Default: 0,
        0 : IPv4,
        1 : IPv6."
   ::= { fgs2528kxSystemTimeNTPEntry 2 }

fgs2528kxSystemTimeNTPServer OBJECT-TYPE
   SYNTAX       DisplayString
   MAX-ACCESS   read-write
   STATUS       current
   DESCRIPTION
       "Get/Set the NTP Time Server1. You can use the IP address or domain name."
   ::= { fgs2528kxSystemTimeNTPEntry 3 }

fgs2528kxSystemTimeNTPCurrentMode OBJECT-TYPE
   SYNTAX      INTEGER (0..3)
   MAX-ACCESS  read-write
   STATUS      current
   DESCRIPTION
       " 0: Empty
        1: Active
        2: Edit
        3: Delete"
   ::= { fgs2528kxSystemTimeNTPEntry 4 }


fgs2528kxSystemAccount                                         OBJECT IDENTIFIER ::= { fgs2528kxSystem 3 }

fgs2528kxSystemAccountUsers                                    OBJECT IDENTIFIER ::= { fgs2528kxSystemAccount 1 }

fgs2528kxSystemAccountUserCreate OBJECT-TYPE
   SYNTAX       INTEGER(0|1)
   MAX-ACCESS   read-write
   STATUS       current
   DESCRIPTION
       "default: 0
        0 : None  (read only)
        1 : Create a user account"
   ::= { fgs2528kxSystemAccountUsers 1 }

fgs2528kxSystemAccountUsersTable OBJECT-TYPE
   SYNTAX      SEQUENCE OF FGS2528KXSystemAccountUsersEntry
   MAX-ACCESS  not-accessible
   STATUS      current
   DESCRIPTION
       " "
   ::= { fgs2528kxSystemAccountUsers 2 }

fgs2528kxSystemAccountUsersEntry OBJECT-TYPE
   SYNTAX      FGS2528KXSystemAccountUsersEntry
   MAX-ACCESS  not-accessible
   STATUS      current
   DESCRIPTION
       ""
   INDEX    { fgs2528kxUserIndex  }
   ::= { fgs2528kxSystemAccountUsersTable 1 }


FGS2528KXSystemAccountUsersEntry ::= SEQUENCE {
   fgs2528kxUserIndex              INTEGER,
   fgs2528kxUserName               DisplayString,
   fgs2528kxPassword               DisplayString,
   fgs2528kxUserPrivilegeLevel     INTEGER,
   fgs2528kxAccountUserRowStatus   INTEGER
}


fgs2528kxUserIndex OBJECT-TYPE
   SYNTAX      INTEGER (1..20)
   MAX-ACCESS  not-accessible
   STATUS      current
   DESCRIPTION
       " "
   ::= { fgs2528kxSystemAccountUsersEntry 1 }

fgs2528kxUserName OBJECT-TYPE
   SYNTAX      DisplayString (SIZE (1..32))
   MAX-ACCESS  read-write
   STATUS      current
   DESCRIPTION
       " "
   ::= { fgs2528kxSystemAccountUsersEntry 2 }

fgs2528kxPassword OBJECT-TYPE
   SYNTAX      DisplayString (SIZE (1..32))
   MAX-ACCESS  read-write
   STATUS      current
   DESCRIPTION
       " "
   ::= { fgs2528kxSystemAccountUsersEntry 3 }

fgs2528kxUserPrivilegeLevel OBJECT-TYPE
   SYNTAX      INTEGER (1..15)
   MAX-ACCESS  read-write
   STATUS      current
   DESCRIPTION
       "default:1
        User privilege level range : 1 - 15"
   ::= { fgs2528kxSystemAccountUsersEntry 4 }

fgs2528kxAccountUserRowStatus OBJECT-TYPE
   SYNTAX      INTEGER (1..5)
   MAX-ACCESS  read-write
   STATUS      current
   DESCRIPTION
       " 1: active
        2: notInservice
        3: edit
        4: destroy
        5: undo"
   ::= { fgs2528kxSystemAccountUsersEntry 5 }

fgs2528kxSystemAccountPrivilegeLevel                           OBJECT IDENTIFIER ::= { fgs2528kxSystemAccount 2 }

fgs2528kxAccountPrivilegeLevel OBJECT-TYPE
   SYNTAX      INTEGER (1..15)
   MAX-ACCESS  read-write
   STATUS      current
   DESCRIPTION
       "Default:10, Range : 1-15. "
   ::= { fgs2528kxSystemAccountPrivilegeLevel 1 }

fgs2528kxAggregationPrivilegeLevel OBJECT-TYPE
   SYNTAX      INTEGER (1..15)
   MAX-ACCESS  read-write
   STATUS      current
   DESCRIPTION
       "Default:10, Range : 1-15. "
   ::= { fgs2528kxSystemAccountPrivilegeLevel 2 }

fgs2528kxDiagnosticsPrivilegeLevel OBJECT-TYPE
   SYNTAX      INTEGER (1..15)
   MAX-ACCESS  read-write
   STATUS      current
   DESCRIPTION
       "Default:10, Range : 1-15. "
   ::= { fgs2528kxSystemAccountPrivilegeLevel 3 }

fgs2528kxEPSPrivilegeLevel OBJECT-TYPE
   SYNTAX      INTEGER (1..15)
   MAX-ACCESS  read-write
   STATUS      current
   DESCRIPTION
       "Default:10, Range : 1-15. "
   ::= { fgs2528kxSystemAccountPrivilegeLevel 5 }

fgs2528kxERPSPrivilegeLevel OBJECT-TYPE
   SYNTAX      INTEGER (1..15)
   MAX-ACCESS  read-write
   STATUS      current
   DESCRIPTION
       "Default:10, Range : 1-15. "
   ::= { fgs2528kxSystemAccountPrivilegeLevel 6 }

fgs2528kxETHLinkOAMPrivilegeLevel OBJECT-TYPE
   SYNTAX      INTEGER (1..15)
   MAX-ACCESS  read-write
   STATUS      current
   DESCRIPTION
       "Default:10, Range : 1-15. "
   ::= { fgs2528kxSystemAccountPrivilegeLevel 7 }

fgs2528kxEVCPrivilegeLevel OBJECT-TYPE
   SYNTAX      INTEGER (1..15)
   MAX-ACCESS  read-write
   STATUS      current
   DESCRIPTION
       "Default:10, Range : 1-15. "
   ::= { fgs2528kxSystemAccountPrivilegeLevel 8 }

fgs2528kxGARPPrivilegeLevel OBJECT-TYPE
   SYNTAX      INTEGER (1..15)
   MAX-ACCESS  read-write
   STATUS      current
   DESCRIPTION
       "Default:10, Range : 1-15. "
   ::= { fgs2528kxSystemAccountPrivilegeLevel 10 }

fgs2528kxGVRPPrivilegeLevel OBJECT-TYPE
   SYNTAX      INTEGER (1..15)
   MAX-ACCESS  read-write
   STATUS      current
   DESCRIPTION
       "Default:10, Range : 1-15. "
   ::= { fgs2528kxSystemAccountPrivilegeLevel 11 }

fgs2528kxIPPrivilegeLevel OBJECT-TYPE
   SYNTAX      INTEGER (1..15)
   MAX-ACCESS  read-write
   STATUS      current
   DESCRIPTION
       "Default:10, Range : 1-15. "
   ::= { fgs2528kxSystemAccountPrivilegeLevel 12 }

fgs2528kxIPMCSnoopingPrivilegeLevel OBJECT-TYPE
   SYNTAX      INTEGER (1..15)
   MAX-ACCESS  read-write
   STATUS      current
   DESCRIPTION
       "Default:10, Range : 1-15. "
   ::= { fgs2528kxSystemAccountPrivilegeLevel 13 }

fgs2528kxLACPPrivilegeLevel OBJECT-TYPE
   SYNTAX      INTEGER (1..15)
   MAX-ACCESS  read-write
   STATUS      current
   DESCRIPTION
       "Default:10, Range : 1-15. "
   ::= { fgs2528kxSystemAccountPrivilegeLevel 14 }

fgs2528kxLLDPPrivilegeLevel OBJECT-TYPE
   SYNTAX      INTEGER (1..15)
   MAX-ACCESS  read-write
   STATUS      current
   DESCRIPTION
       "Default:10, Range : 1-15. "
   ::= { fgs2528kxSystemAccountPrivilegeLevel 15 }

fgs2528kxLLDPMEDPrivilegeLevel OBJECT-TYPE
   SYNTAX      INTEGER (1..15)
   MAX-ACCESS  read-write
   STATUS      current
   DESCRIPTION
       "Default:10, Range : 1-15. "
   ::= { fgs2528kxSystemAccountPrivilegeLevel 16 }

fgs2528kxLoopProtectPrivilegeLevel OBJECT-TYPE
   SYNTAX      INTEGER (1..15)
   MAX-ACCESS  read-write
   STATUS      current
   DESCRIPTION
       "Default:10, Range : 1-15. "
   ::= { fgs2528kxSystemAccountPrivilegeLevel 17 }

fgs2528kxMACTablePrivilegeLevel OBJECT-TYPE
   SYNTAX      INTEGER (1..15)
   MAX-ACCESS  read-write
   STATUS      current
   DESCRIPTION
       "Default:10, Range : 1-15. "
   ::= { fgs2528kxSystemAccountPrivilegeLevel 18 }

fgs2528kxMEPPrivilegeLevel OBJECT-TYPE
   SYNTAX      INTEGER (1..15)
   MAX-ACCESS  read-write
   STATUS      current
   DESCRIPTION
       "Default:10, Range : 1-15. "
   ::= { fgs2528kxSystemAccountPrivilegeLevel 20 }

fgs2528kxMVRPrivilegeLevel OBJECT-TYPE
   SYNTAX      INTEGER (1..15)
   MAX-ACCESS  read-write
   STATUS      current
   DESCRIPTION
       "Default:10, Range : 1-15. "
   ::= { fgs2528kxSystemAccountPrivilegeLevel 22 }

fgs2528kxMaintenancePrivilegeLevel OBJECT-TYPE
   SYNTAX      INTEGER (1..15)
   MAX-ACCESS  read-write
   STATUS      current
   DESCRIPTION
       "Default:10, Range : 1-15. "
   ::= { fgs2528kxSystemAccountPrivilegeLevel 24 }

fgs2528kxMirroringPrivilegeLevel OBJECT-TYPE
   SYNTAX      INTEGER (1..15)
   MAX-ACCESS  read-write
   STATUS      current
   DESCRIPTION
       "Default:10, Range : 1-15. "
   ::= { fgs2528kxSystemAccountPrivilegeLevel 25 }

fgs2528kxPTPPrivilegeLevel OBJECT-TYPE
   SYNTAX      INTEGER (1..15)
   MAX-ACCESS  read-write
   STATUS      current
   DESCRIPTION
       "Default:10, Range : 1-15. "
   ::= { fgs2528kxSystemAccountPrivilegeLevel 26 }

fgs2528kxPortsPrivilegeLevel OBJECT-TYPE
   SYNTAX      INTEGER (1..15)
   MAX-ACCESS  read-write
   STATUS      current
   DESCRIPTION
       "Default:10, Range : 1-15. "
   ::= { fgs2528kxSystemAccountPrivilegeLevel 27 }

fgs2528kxPrivateVLANsPrivilegeLevel OBJECT-TYPE
   SYNTAX      INTEGER (1..15)
   MAX-ACCESS  read-write
   STATUS      current
   DESCRIPTION
       "Default:10, Range : 1-15. "
   ::= { fgs2528kxSystemAccountPrivilegeLevel 28 }

fgs2528kxQoSPrivilegeLevel OBJECT-TYPE
   SYNTAX      INTEGER (1..15)
   MAX-ACCESS  read-write
   STATUS      current
   DESCRIPTION
       "Default:10, Range : 1-15. "
   ::= { fgs2528kxSystemAccountPrivilegeLevel 29 }

fgs2528kxSMTPPrivilegeLevel OBJECT-TYPE
   SYNTAX      INTEGER (1..15)
   MAX-ACCESS  read-write
   STATUS      current
   DESCRIPTION
       "Default:10, Range : 1-15. "
   ::= { fgs2528kxSystemAccountPrivilegeLevel 31 }

fgs2528kxSNMPPrivilegeLevel OBJECT-TYPE
   SYNTAX      INTEGER (1..15)
   MAX-ACCESS  read-write
   STATUS      current
   DESCRIPTION
       "Default:10, Range : 1-15. "
   ::= { fgs2528kxSystemAccountPrivilegeLevel 32 }

fgs2528kxSecurityPrivilegeLevel OBJECT-TYPE
   SYNTAX      INTEGER (1..15)
   MAX-ACCESS  read-write
   STATUS      current
   DESCRIPTION
       "Default:10, Range : 1-15. "
   ::= { fgs2528kxSystemAccountPrivilegeLevel 33 }

fgs2528kxSpanningTreePrivilegeLevel OBJECT-TYPE
   SYNTAX      INTEGER (1..15)
   MAX-ACCESS  read-write
   STATUS      current
   DESCRIPTION
       "Default:10, Range : 1-15. "
   ::= { fgs2528kxSystemAccountPrivilegeLevel 35 }

fgs2528kxSystemPrivilegeLevel OBJECT-TYPE
   SYNTAX      INTEGER (1..15)
   MAX-ACCESS  read-write
   STATUS      current
   DESCRIPTION
       "Default:10, Range : 1-15. "
   ::= { fgs2528kxSystemAccountPrivilegeLevel 36 }

fgs2528kxTrapEventPrivilegeLevel OBJECT-TYPE
   SYNTAX      INTEGER (1..15)
   MAX-ACCESS  read-write
   STATUS      current
   DESCRIPTION
       "Default:10, Range : 1-15. "
   ::= { fgs2528kxSystemAccountPrivilegeLevel 37 }

fgs2528kxVCLPrivilegeLevel OBJECT-TYPE
   SYNTAX      INTEGER (1..15)
   MAX-ACCESS  read-write
   STATUS      current
   DESCRIPTION
       "Default:10, Range : 1-15. "
   ::= { fgs2528kxSystemAccountPrivilegeLevel 39 }

fgs2528kxVLANTranslationPrivilegeLevel OBJECT-TYPE
   SYNTAX      INTEGER (1..15)
   MAX-ACCESS  read-write
   STATUS      current
   DESCRIPTION
       "Default:10, Range : 1-15. "
   ::= { fgs2528kxSystemAccountPrivilegeLevel 40 }

fgs2528kxVLANsPrivilegeLevel OBJECT-TYPE
   SYNTAX      INTEGER (1..15)
   MAX-ACCESS  read-write
   STATUS      current
   DESCRIPTION
       "Default:10, Range : 1-15. "
   ::= { fgs2528kxSystemAccountPrivilegeLevel 41 }


fgs2528kxIP                                                    OBJECT IDENTIFIER ::= { fgs2528kxSystem 4 }

fgs2528kxIPv4                                                  OBJECT IDENTIFIER ::= { fgs2528kxIP 1 }

fgs2528kxIPv4Configured                                                  OBJECT IDENTIFIER ::= { fgs2528kxIPv4 1 }

fgs2528kxIpv4DHCPClient OBJECT-TYPE
   SYNTAX      INTEGER (0|1)
   MAX-ACCESS  read-write
   STATUS      current
   DESCRIPTION
       "default:0
       0: disable
       1: enable"
   ::= { fgs2528kxIPv4Configured 1 }

fgs2528kxIPv4Address OBJECT-TYPE
   SYNTAX      IpAddress
   MAX-ACCESS  read-write
   STATUS      current
   DESCRIPTION
       ""
   ::= { fgs2528kxIPv4Configured 2 }

fgs2528kxIPv4Mask OBJECT-TYPE
   SYNTAX      IpAddress
   MAX-ACCESS  read-write
   STATUS      current
   DESCRIPTION
       ""
   ::= { fgs2528kxIPv4Configured 3 }

fgs2528kxIPv4Router OBJECT-TYPE
   SYNTAX      IpAddress
   MAX-ACCESS  read-write
   STATUS      current
   DESCRIPTION
       ""
   ::= { fgs2528kxIPv4Configured 4 }

fgs2528kxIPv4VLANId OBJECT-TYPE
   SYNTAX      INTEGER (1..4094)
   MAX-ACCESS  read-write
   STATUS      current
   DESCRIPTION
       "default:1"
   ::= { fgs2528kxIPv4Configured 5 }

fgs2528kxIPv4DNSServer OBJECT-TYPE
   SYNTAX      IpAddress
   MAX-ACCESS  read-write
   STATUS      current
   DESCRIPTION
       ""
   ::= { fgs2528kxIPv4Configured 6 }

fgs2528kxIPv4DNSProxy OBJECT-TYPE
   SYNTAX      INTEGER (0|1)
   MAX-ACCESS  read-write
   STATUS      current
   DESCRIPTION
       " "
   ::= { fgs2528kxIPv4Configured 7 }

fgs2528kxIPv4Current                                                  OBJECT IDENTIFIER ::= { fgs2528kxIPv4 2 }

fgs2528kxIpv4CurrentDHCPClient OBJECT-TYPE
   SYNTAX      INTEGER (0|1)
   MAX-ACCESS  read-write
   STATUS      current
   DESCRIPTION
       "default:0
       0: none (for read)
       1: renew"
   ::= { fgs2528kxIPv4Current 1 }

fgs2528kxIPv4CurrentAddress OBJECT-TYPE
   SYNTAX      IpAddress
   MAX-ACCESS  read-only
   STATUS      current
   DESCRIPTION
       ""
   ::= { fgs2528kxIPv4Current 2 }

fgs2528kxIPv4CurrentMask OBJECT-TYPE
   SYNTAX      IpAddress
   MAX-ACCESS  read-only
   STATUS      current
   DESCRIPTION
       ""
   ::= { fgs2528kxIPv4Current 3 }

fgs2528kxIPv4CurrentRouter OBJECT-TYPE
   SYNTAX      IpAddress
   MAX-ACCESS  read-only
   STATUS      current
   DESCRIPTION
       ""
   ::= { fgs2528kxIPv4Current 4 }

fgs2528kxIPv4CurrentVLANId OBJECT-TYPE
   SYNTAX      INTEGER (1..4094)
   MAX-ACCESS  read-only
   STATUS      current
   DESCRIPTION
       "default:1"
   ::= { fgs2528kxIPv4Current 5 }

fgs2528kxIPv4CurrentDNSServer OBJECT-TYPE
   SYNTAX      IpAddress
   MAX-ACCESS  read-only
   STATUS      current
   DESCRIPTION
       ""
   ::= { fgs2528kxIPv4Current 6 }


fgs2528kxIPv6                                                  OBJECT IDENTIFIER ::= { fgs2528kxIP 2 }

fgs2528kxIPv6Configured                                                  OBJECT IDENTIFIER ::= { fgs2528kxIPv6 1 }

fgs2528kxIpv6AutoConfiguration OBJECT-TYPE
   SYNTAX      INTEGER (0|1)
   MAX-ACCESS  read-write
   STATUS      current
   DESCRIPTION
       "default:0
       0: disable
       1: enable"
   ::= { fgs2528kxIPv6Configured 1 }

fgs2528kxIpv6Address OBJECT-TYPE
   SYNTAX      DisplayString (SIZE (0..30))
   MAX-ACCESS  read-write
   STATUS      current
   DESCRIPTION
       ""
   ::= { fgs2528kxIPv6Configured 2 }

fgs2528kxIpv6Prefix OBJECT-TYPE
   SYNTAX      INTEGER (1..128)
   MAX-ACCESS  read-write
   STATUS      current
   DESCRIPTION
       "default: 96"
   ::= { fgs2528kxIPv6Configured 3 }

fgs2528kxIpv6Router OBJECT-TYPE
   SYNTAX      DisplayString (SIZE (0..30))
   MAX-ACCESS  read-write
   STATUS      current
   DESCRIPTION
       " "
   ::= { fgs2528kxIPv6Configured 4 }

fgs2528kxIPv6Current                                                  OBJECT IDENTIFIER ::= { fgs2528kxIPv6 2 }

fgs2528kxIpv6CurrentAutoConfiguration OBJECT-TYPE
   SYNTAX      INTEGER (0|1)
   MAX-ACCESS  read-only
   STATUS      current
   DESCRIPTION
       "default:0
       0: disable
       1: enable"
   ::= { fgs2528kxIPv6Current 1 }

fgs2528kxIpv6CurrentAddress OBJECT-TYPE
   SYNTAX      DisplayString (SIZE (0..30))
   MAX-ACCESS  read-only
   STATUS      current
   DESCRIPTION
       ""
   ::= { fgs2528kxIPv6Current 2 }


fgs2528kxIpv6CurrentLinkLocalAddress OBJECT-TYPE
   SYNTAX      DisplayString(SIZE (0..30))
   MAX-ACCESS  read-only
   STATUS      current
   DESCRIPTION
       ""
   ::= { fgs2528kxIPv6Current 3 }


fgs2528kxIpv6CurrentPrefix OBJECT-TYPE
   SYNTAX      INTEGER (1..128)
   MAX-ACCESS  read-only
   STATUS      current
   DESCRIPTION
       ""
   ::= { fgs2528kxIPv6Current 4 }

fgs2528kxIpv6CurrentRouter OBJECT-TYPE
   SYNTAX      DisplayString (SIZE (0..30))
   MAX-ACCESS  read-only
   STATUS      current
   DESCRIPTION
       " "
   ::= { fgs2528kxIPv6Current 5 }

fgs2528kxSyslog                                                OBJECT IDENTIFIER ::= { fgs2528kxSystem 5 }

fgs2528kxSyslogConf                                            OBJECT IDENTIFIER ::= { fgs2528kxSyslog 1 }

fgs2528kxServerMode OBJECT-TYPE
   SYNTAX      INTEGER (0|1)
   MAX-ACCESS  read-write
   STATUS      current
   DESCRIPTION
       "default: 0
       0: disable
       1: enable "
   ::= { fgs2528kxSyslogConf 1 }

fgs2528kxServerAddress1 OBJECT-TYPE
   SYNTAX      IpAddress
   MAX-ACCESS  read-write
   STATUS      current
   DESCRIPTION
       " "
   ::= { fgs2528kxSyslogConf 2 }

fgs2528kxServerAddress2 OBJECT-TYPE
   SYNTAX      IpAddress
   MAX-ACCESS  read-write
   STATUS      current
   DESCRIPTION
       " "
   ::= { fgs2528kxSyslogConf 3 }

fgs2528kxSyslogLevel OBJECT-TYPE
   SYNTAX      INTEGER(0..7)
   MAX-ACCESS  read-write
   STATUS      current
   DESCRIPTION
       "default: 6 (Info)
       0: Emergency
       1: Alert
       2: Critical
       3: Error
       4: Warning
       5: Notice
       6: Info
       7: Debug"
   ::= { fgs2528kxSyslogConf 4 }

fgs2528kxSyslogDetailedInfo                                    OBJECT IDENTIFIER ::= { fgs2528kxSyslog 2 }

fgs2528kxSyslogDetailedInfoClear OBJECT-TYPE
   SYNTAX      INTEGER(0|1)
   MAX-ACCESS  read-write
   STATUS      current
   DESCRIPTION
      "default: 0
       0 : None  (read only)
       1 : Clear Syslog"
   ::= { fgs2528kxSyslogDetailedInfo 1 }

fgs2528kxSyslogDetailedInfoTable OBJECT-TYPE
  SYNTAX      SEQUENCE OF FGS2528KXSyslogDetailedInfoEntry
  MAX-ACCESS  not-accessible
  STATUS      current
  DESCRIPTION
           " "
       ::= { fgs2528kxSyslogDetailedInfo 2 }

fgs2528kxSyslogDetailedInfoEntry OBJECT-TYPE
   SYNTAX      FGS2528KXSyslogDetailedInfoEntry
   MAX-ACCESS  not-accessible
   STATUS      current
   DESCRIPTION
           ""
   INDEX    { fgs2528kxSyslogDetailedInfoIndex  }
   ::= { fgs2528kxSyslogDetailedInfoTable 1 }

FGS2528KXSyslogDetailedInfoEntry ::= SEQUENCE {
   fgs2528kxSyslogDetailedInfoIndex       INTEGER,
   fgs2528kxSyslogDetailedInfoLevel       DisplayString,
   fgs2528kxSyslogDetailedInfoTime        DisplayString,
   fgs2528kxSyslogDetailedInfoMessage     DisplayString
}

fgs2528kxSyslogDetailedInfoIndex OBJECT-TYPE
   SYNTAX      INTEGER (1..1024)
   MAX-ACCESS  not-accessible
   STATUS      current
   DESCRIPTION
       " "
   ::= { fgs2528kxSyslogDetailedInfoEntry 1 }

fgs2528kxSyslogDetailedInfoLevel OBJECT-TYPE
   SYNTAX      DisplayString
   MAX-ACCESS  read-only
   STATUS      current
   DESCRIPTION
       " "
   ::= { fgs2528kxSyslogDetailedInfoEntry 2 }

fgs2528kxSyslogDetailedInfoTime OBJECT-TYPE
   SYNTAX      DisplayString(SIZE (0..20))
   MAX-ACCESS  read-only
   STATUS      current
   DESCRIPTION
       " "
   ::= { fgs2528kxSyslogDetailedInfoEntry 3 }

fgs2528kxSyslogDetailedInfoMessage OBJECT-TYPE
   SYNTAX      DisplayString
   MAX-ACCESS  read-only
   STATUS      current
   DESCRIPTION
       " "
   ::= { fgs2528kxSyslogDetailedInfoEntry 4 }


fgs2528kxSnmp                                                OBJECT IDENTIFIER ::= { fgs2528kxSystem 6 }

fgs2528kxSnmpConf                                            OBJECT IDENTIFIER ::= { fgs2528kxSnmp 1 }

fgs2528kxGetCommunity OBJECT-TYPE
   SYNTAX       DisplayString
   MAX-ACCESS   read-write
   STATUS       current
   DESCRIPTION
       "Get/Set the get-community of the SNMP."
   ::= { fgs2528kxSnmpConf 1 }

fgs2528kxSetCommunityMode OBJECT-TYPE
   SYNTAX       INTEGER(0|1)
   MAX-ACCESS   read-write
   STATUS       current
   DESCRIPTION
       "Get/Set the set-community mode of the SNMP.
        default : 1, 0: disable, 1: enable. "
   ::= { fgs2528kxSnmpConf 2 }

fgs2528kxSetCommunity OBJECT-TYPE
   SYNTAX       DisplayString
   MAX-ACCESS   read-write
   STATUS       current
   DESCRIPTION
       "Get/Set the set-community of the SNMP."
   ::= { fgs2528kxSnmpConf 3 }

fgs2528kxTrapHostConfTable OBJECT-TYPE
   SYNTAX      SEQUENCE OF FGS2528KXTrapHostConfEntry
   MAX-ACCESS  not-accessible
   STATUS      current
   DESCRIPTION
       "A list of trap host entry. The numbers of entries are given by the value of fgs2528kxTrapHostConfNumber."
   ::= { fgs2528kxSnmpConf 4 }

fgs2528kxTrapHostConfEntry OBJECT-TYPE
   SYNTAX      FGS2528KXTrapHostConfEntry
   MAX-ACCESS  not-accessible
   STATUS      current
   DESCRIPTION
       "This is the entry information for trap host."
   INDEX    { fgs2528kxTrapHostConfIndex  }
   ::= { fgs2528kxTrapHostConfTable 1 }

FGS2528KXTrapHostConfEntry ::= SEQUENCE {
    fgs2528kxTrapHostConfIndex             INTEGER,
    fgs2528kxTrapHostConfVersion           INTEGER,
    fgs2528kxTrapHostConfIPType            INTEGER,
    fgs2528kxTrapHostConfIP                DisplayString,
    fgs2528kxTrapHostConfPort              INTEGER,
    fgs2528kxTrapHostConfCommunity         DisplayString,
    fgs2528kxTrapHostConfSeverityLevel     INTEGER,
    fgs2528kxTrapHostConfSecurityLevel     INTEGER,
    fgs2528kxTrapHostConfAuthPtc           INTEGER,
    fgs2528kxTrapHostConfAuthPassword      DisplayString,
    fgs2528kxTrapHostConfPrivPtc           INTEGER,
    fgs2528kxTrapHostConfPrivPassword      DisplayString,
    fgs2528kxTrapHostConfCurrentMode       INTEGER
}

fgs2528kxTrapHostConfIndex OBJECT-TYPE
   SYNTAX      INTEGER (1..6)
   MAX-ACCESS  not-accessible
   STATUS      current
   DESCRIPTION
       " The index of the trap host entry. "
   ::= { fgs2528kxTrapHostConfEntry 1 }

fgs2528kxTrapHostConfVersion OBJECT-TYPE
   SYNTAX       INTEGER(2..3)
   MAX-ACCESS   read-write
   STATUS       current
   DESCRIPTION
       "The version of the Trap PDU. Version : 2(SNMPv2c), 3(SNMPv3)"
   ::= { fgs2528kxTrapHostConfEntry 2 }

fgs2528kxTrapHostConfIPType OBJECT-TYPE
   SYNTAX       INTEGER(4|6)
   MAX-ACCESS   read-write
   STATUS       current
   DESCRIPTION
       "Server IP Type. Default: 4,
        4 : IPv4,
        6 : IPv6."
   ::= { fgs2528kxTrapHostConfEntry 3 }

fgs2528kxTrapHostConfIP OBJECT-TYPE
   SYNTAX       DisplayString
   MAX-ACCESS   read-write
   STATUS       current
   DESCRIPTION
       "This is the IP of the trap host."
   ::= { fgs2528kxTrapHostConfEntry 4 }

fgs2528kxTrapHostConfPort OBJECT-TYPE
   SYNTAX       INTEGER(1..65535)
   MAX-ACCESS   read-write
   STATUS       current
   DESCRIPTION
       "This is the receiving-port number of the trap host.
        range : 1 - 65535."
   ::= { fgs2528kxTrapHostConfEntry 5 }

fgs2528kxTrapHostConfCommunity OBJECT-TYPE
   SYNTAX       DisplayString (SIZE (1..32))
   MAX-ACCESS   read-write
   STATUS       current
   DESCRIPTION
       "The community/security name for the trap PDU."
   ::= { fgs2528kxTrapHostConfEntry 6 }

fgs2528kxTrapHostConfSeverityLevel	OBJECT-TYPE
   SYNTAX       INTEGER(0..7)
   MAX-ACCESS   read-write
   STATUS       current
   DESCRIPTION
       "The Severity Level.
        0 : Emerg, 1 : Alert, 2 : Crit, 3 : Error, 4 : Warning, 5 : Notice, 6 : Info, 7 : Debug."
	::= { fgs2528kxTrapHostConfEntry 7 }

fgs2528kxTrapHostConfSecurityLevel	OBJECT-TYPE
   SYNTAX       INTEGER(1..3)
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { fgs2528kxTrapHostConfEntry 8 }

fgs2528kxTrapHostConfAuthPtc	OBJECT-TYPE
   SYNTAX       INTEGER(1..2)
   MAX-ACCESS   read-write
   STATUS       current
   DESCRIPTION
       "Authentication Protocol, there are SHA and MD5 supported presently.
        1 : MD5, 2 : SHA."
	::= { fgs2528kxTrapHostConfEntry 9 }

fgs2528kxTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { fgs2528kxTrapHostConfEntry 10 }

fgs2528kxTrapHostConfPrivPtc	OBJECT-TYPE
   SYNTAX       INTEGER(1)
   MAX-ACCESS   read-write
   STATUS       current
   DESCRIPTION
       "This is the Privacy Protocol, which is used in AuthPriv. Only supports DES.
        An empty string will be returned if the security level is not 3(AuthPriv).
        1 : DES."
	::= { fgs2528kxTrapHostConfEntry 11 }

fgs2528kxTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { fgs2528kxTrapHostConfEntry 12 }

fgs2528kxTrapHostConfCurrentMode OBJECT-TYPE
   SYNTAX       INTEGER(0..2)
   MAX-ACCESS   read-write
   STATUS       current
   DESCRIPTION
       "0:Empty, 1:Active mode, 2:Edit mode, 3:Delete."
   ::= { fgs2528kxTrapHostConfEntry 13 }


----------------------------------------------------------------------------------------------------

fgs2528kxConfiguration                                         OBJECT IDENTIFIER ::= { fgs2528kxProductId 2 }

fgs2528kxPort                                                  OBJECT IDENTIFIER ::= { fgs2528kxConfiguration 1 }

fgs2528kxPortConfigurationTable OBJECT-TYPE
   SYNTAX      SEQUENCE OF FGS2528KXPortConfigurationEntry
   MAX-ACCESS  not-accessible
   STATUS      current
   DESCRIPTION
       " Show port configurations. "
   ::= { fgs2528kxPort 1 }

fgs2528kxPortConfigurationEntry OBJECT-TYPE
   SYNTAX      FGS2528KXPortConfigurationEntry
   MAX-ACCESS  not-accessible
   STATUS      current
   DESCRIPTION
       ""
   INDEX    { fgs2528kxPortConfPort  }
   ::= { fgs2528kxPortConfigurationTable 1 }

FGS2528KXPortConfigurationEntry ::= SEQUENCE {
   fgs2528kxPortConfPort                     INTEGER,
   fgs2528kxPortConfPortMedia                DisplayString,
   fgs2528kxPortConfLink                     DisplayString,
   fgs2528kxPortConfCurrentSpeed             DisplayString,
   fgs2528kxPortConfSpeed                    INTEGER,
   fgs2528kxPortConfCurrentFlowControlRx     INTEGER,
   fgs2528kxPortConfCurrentFlowControlTx     INTEGER,
   fgs2528kxPortConfFlowControl              INTEGER,
   fgs2528kxPortConfMaxFrameSize             INTEGER,
   fgs2528kxPortConfExcessiveCollisionMode   INTEGER,
   fgs2528kxPortConfPowerControl             INTEGER,
   fgs2528kxPortConfDescription              DisplayString
}

fgs2528kxPortConfPort OBJECT-TYPE
   SYNTAX      INTEGER (1..4095)
   MAX-ACCESS  not-accessible
   STATUS      current
   DESCRIPTION
       " port, range : 1 - port number. "
   ::= { fgs2528kxPortConfigurationEntry 1 }

fgs2528kxPortConfPortMedia OBJECT-TYPE
   SYNTAX      DisplayString(SIZE (1..4))
   MAX-ACCESS  read-only
   STATUS      current
   DESCRIPTION
       " Show port media. "
   ::= { fgs2528kxPortConfigurationEntry 2 }

fgs2528kxPortConfLink OBJECT-TYPE
   SYNTAX      DisplayString(SIZE (2..4))
   MAX-ACCESS  read-only
   STATUS      current
   DESCRIPTION
       " The current link state. "
   ::= { fgs2528kxPortConfigurationEntry 3 }

fgs2528kxPortConfCurrentSpeed OBJECT-TYPE
   SYNTAX      DisplayString(SIZE (6..12))
   MAX-ACCESS  read-only
   STATUS      current
   DESCRIPTION
       " The current link speed of the port. "
   ::= { fgs2528kxPortConfigurationEntry 4 }

fgs2528kxPortConfSpeed OBJECT-TYPE
   SYNTAX      INTEGER (0..11)
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X "
   ::= { fgs2528kxPortConfigurationEntry 5 }

fgs2528kxPortConfCurrentFlowControlRx OBJECT-TYPE
   SYNTAX      INTEGER (0|1)
   MAX-ACCESS  read-only
   STATUS      current
   DESCRIPTION
       "0: disable
        1: enable
        2: not support.  "
   ::= { fgs2528kxPortConfigurationEntry 6 }

fgs2528kxPortConfCurrentFlowControlTx OBJECT-TYPE
   SYNTAX      INTEGER (0|1)
   MAX-ACCESS  read-only
   STATUS      current
   DESCRIPTION
       "0: disable
        1: enable
        2: not support.  "
   ::= { fgs2528kxPortConfigurationEntry 7 }

fgs2528kxPortConfFlowControl OBJECT-TYPE
   SYNTAX      INTEGER (0|1)
   MAX-ACCESS  read-write
   STATUS      current
   DESCRIPTION
       "default: 0,
        0: disable
        1: enable
        2: not support. "
   ::= { fgs2528kxPortConfigurationEntry 8 }

fgs2528kxPortConfMaxFrameSize OBJECT-TYPE
   SYNTAX      INTEGER (1518..9600)
   MAX-ACCESS  read-write
   STATUS      current
   DESCRIPTION
       "default: 9600 , range : 1518 - 9600 "
   ::= { fgs2528kxPortConfigurationEntry 9 }

fgs2528kxPortConfExcessiveCollisionMode OBJECT-TYPE
   SYNTAX      INTEGER (0|1)
   MAX-ACCESS  read-write
   STATUS      current
   DESCRIPTION
       "default: 0,
        Excessive Collision Mode :
        0: Discard,
        1: Restart,
        2: not support.
       "
   ::= { fgs2528kxPortConfigurationEntry 10 }

fgs2528kxPortConfPowerControl OBJECT-TYPE
   SYNTAX      INTEGER (0..3)
   MAX-ACCESS  read-write
   STATUS      current
   DESCRIPTION
       "default: 0,
        PowerControl :
        0: disable,
        1: Actiphy,
        2: Dynamic (perfectReach),
        3: Enable,
        4: not support.
       "
   ::= { fgs2528kxPortConfigurationEntry 11 }

fgs2528kxPortConfDescription OBJECT-TYPE
   SYNTAX      DisplayString
   MAX-ACCESS  read-write
   STATUS      current
   DESCRIPTION
       " Interface specific description.
         Up to 47 characters describing this interface. "
   ::= { fgs2528kxPortConfigurationEntry 12 }


fgs2528kxPortTrafficStatisticsTable OBJECT-TYPE
   SYNTAX      SEQUENCE OF FGS2528KXPortTrafficStatisticsEntry
   MAX-ACCESS  not-accessible
   STATUS      current
   DESCRIPTION
       " "
   ::= { fgs2528kxPort 2 }

fgs2528kxPortTrafficStatisticsEntry OBJECT-TYPE
   SYNTAX      FGS2528KXPortTrafficStatisticsEntry
   MAX-ACCESS  not-accessible
   STATUS      current
   DESCRIPTION
       ""
   INDEX    { fgs2528kxPortTrafficStatisticsPort  }
   ::= { fgs2528kxPortTrafficStatisticsTable 1 }

FGS2528KXPortTrafficStatisticsEntry ::= SEQUENCE {
   fgs2528kxPortTrafficStatisticsPort          INTEGER,
   fgs2528kxPortTrafficStatisticsClear         INTEGER,
   fgs2528kxPortTrafficRxPackets               Counter64,
   fgs2528kxPortTrafficRxOctets                Counter64,
   fgs2528kxPortTrafficRxUnicast               Counter64,
   fgs2528kxPortTrafficRxMulticast             Counter64,
   fgs2528kxPortTrafficRxBroadcast             Counter64,
   fgs2528kxPortTrafficRxPause                 Counter64,
   fgs2528kxPortTrafficRx64Bytes               Counter64,
   fgs2528kxPortTrafficRx65to127Bytes          Counter64,
   fgs2528kxPortTrafficRx128to255Bytes         Counter64,
   fgs2528kxPortTrafficRx256to511Bytes         Counter64,
   fgs2528kxPortTrafficRx512to1023Bytes        Counter64,
   fgs2528kxPortTrafficRx1024to1526Bytes       Counter64,
   fgs2528kxPortTrafficRxExceecd1527Bytes      Counter64,
   fgs2528kxPortTrafficRxQ0                    Counter64,
   fgs2528kxPortTrafficRxQ1                    Counter64,
   fgs2528kxPortTrafficRxQ2                    Counter64,
   fgs2528kxPortTrafficRxQ3                    Counter64,
   fgs2528kxPortTrafficRxQ4                    Counter64,
   fgs2528kxPortTrafficRxQ5                    Counter64,
   fgs2528kxPortTrafficRxQ6                    Counter64,
   fgs2528kxPortTrafficRxQ7                    Counter64,
   fgs2528kxPortTrafficRxDrops                 Counter64,
   fgs2528kxPortTrafficRxCRCorAlignment        Counter64,
   fgs2528kxPortTrafficRxUndersize             Counter64,
   fgs2528kxPortTrafficRxOversize              Counter64,
   fgs2528kxPortTrafficRxFragments             Counter64,
   fgs2528kxPortTrafficRxJabber                Counter64,
   fgs2528kxPortTrafficRxFiltered              Counter64,
   fgs2528kxPortTrafficTxPackets               Counter64,
   fgs2528kxPortTrafficTxOctets                Counter64,
   fgs2528kxPortTrafficTxUnicast               Counter64,
   fgs2528kxPortTrafficTxMulticast             Counter64,
   fgs2528kxPortTrafficTxBroadcast             Counter64,
   fgs2528kxPortTrafficTxPause                 Counter64,
   fgs2528kxPortTrafficTx64Bytes               Counter64,
   fgs2528kxPortTrafficTx65to127Bytes          Counter64,
   fgs2528kxPortTrafficTx128to255Bytes         Counter64,
   fgs2528kxPortTrafficTx256to511Bytes         Counter64,
   fgs2528kxPortTrafficTx512to1023Bytes        Counter64,
   fgs2528kxPortTrafficTx1024to1526Bytes       Counter64,
   fgs2528kxPortTrafficTxExceecd1527Bytes      Counter64,
   fgs2528kxPortTrafficTxQ0                    Counter64,
   fgs2528kxPortTrafficTxQ1                    Counter64,
   fgs2528kxPortTrafficTxQ2                    Counter64,
   fgs2528kxPortTrafficTxQ3                    Counter64,
   fgs2528kxPortTrafficTxQ4                    Counter64,
   fgs2528kxPortTrafficTxQ5                    Counter64,
   fgs2528kxPortTrafficTxQ6                    Counter64,
   fgs2528kxPortTrafficTxQ7                    Counter64,
   fgs2528kxPortTrafficTxDrops                 Counter64,
   fgs2528kxPortTrafficTxLateOrExcColl         Counter64
}

fgs2528kxPortTrafficStatisticsPort OBJECT-TYPE
   SYNTAX      INTEGER (1..4095)
   MAX-ACCESS  not-accessible
   STATUS      current
   DESCRIPTION
       " "
   ::= { fgs2528kxPortTrafficStatisticsEntry 1 }

fgs2528kxPortTrafficStatisticsClear OBJECT-TYPE
   SYNTAX      INTEGER(0|1)
   MAX-ACCESS  read-write
   STATUS      current
   DESCRIPTION
       " "
   ::= { fgs2528kxPortTrafficStatisticsEntry 2 }

fgs2528kxPortTrafficRxPackets OBJECT-TYPE
   SYNTAX      Counter64
   MAX-ACCESS  read-only
   STATUS      current
   DESCRIPTION
       " "
   ::= { fgs2528kxPortTrafficStatisticsEntry 3 }

fgs2528kxPortTrafficRxOctets OBJECT-TYPE
   SYNTAX      Counter64
   MAX-ACCESS  read-only
   STATUS      current
   DESCRIPTION
       " "
   ::= { fgs2528kxPortTrafficStatisticsEntry 4 }

fgs2528kxPortTrafficRxUnicast OBJECT-TYPE
   SYNTAX      Counter64
   MAX-ACCESS  read-only
   STATUS      current
   DESCRIPTION
       " "
   ::= { fgs2528kxPortTrafficStatisticsEntry 5 }

fgs2528kxPortTrafficRxMulticast OBJECT-TYPE
   SYNTAX      Counter64
   MAX-ACCESS  read-only
   STATUS      current
   DESCRIPTION
       " "
   ::= { fgs2528kxPortTrafficStatisticsEntry 6 }

fgs2528kxPortTrafficRxBroadcast OBJECT-TYPE
   SYNTAX      Counter64
   MAX-ACCESS  read-only
   STATUS      current
   DESCRIPTION
       " "
   ::= { fgs2528kxPortTrafficStatisticsEntry 7 }

fgs2528kxPortTrafficRxPause OBJECT-TYPE
   SYNTAX      Counter64
   MAX-ACCESS  read-only
   STATUS      current
   DESCRIPTION
       " "
   ::= { fgs2528kxPortTrafficStatisticsEntry 8 }

fgs2528kxPortTrafficRx64Bytes OBJECT-TYPE
   SYNTAX      Counter64
   MAX-ACCESS  read-only
   STATUS      current
   DESCRIPTION
       " "
   ::= { fgs2528kxPortTrafficStatisticsEntry 9 }

fgs2528kxPortTrafficRx65to127Bytes OBJECT-TYPE
   SYNTAX      Counter64
   MAX-ACCESS  read-only
   STATUS      current
   DESCRIPTION
       " "
   ::= { fgs2528kxPortTrafficStatisticsEntry 10 }

fgs2528kxPortTrafficRx128to255Bytes OBJECT-TYPE
   SYNTAX      Counter64
   MAX-ACCESS  read-only
   STATUS      current
   DESCRIPTION
       " "
   ::= { fgs2528kxPortTrafficStatisticsEntry 11 }

fgs2528kxPortTrafficRx256to511Bytes OBJECT-TYPE
   SYNTAX      Counter64
   MAX-ACCESS  read-only
   STATUS      current
   DESCRIPTION
       " "
   ::= { fgs2528kxPortTrafficStatisticsEntry 12 }

fgs2528kxPortTrafficRx512to1023Bytes OBJECT-TYPE
   SYNTAX      Counter64
   MAX-ACCESS  read-only
   STATUS      current
   DESCRIPTION
       " "
   ::= { fgs2528kxPortTrafficStatisticsEntry 13 }

fgs2528kxPortTrafficRx1024to1526Bytes OBJECT-TYPE
   SYNTAX      Counter64
   MAX-ACCESS  read-only
   STATUS      current
   DESCRIPTION
       " "
   ::= { fgs2528kxPortTrafficStatisticsEntry 14 }

fgs2528kxPortTrafficRxExceecd1527Bytes OBJECT-TYPE
   SYNTAX      Counter64
   MAX-ACCESS  read-only
   STATUS      current
   DESCRIPTION
       " "
   ::= { fgs2528kxPortTrafficStatisticsEntry 15 }

fgs2528kxPortTrafficRxQ0 OBJECT-TYPE
   SYNTAX      Counter64
   MAX-ACCESS  read-only
   STATUS      current
   DESCRIPTION
       " "
   ::= { fgs2528kxPortTrafficStatisticsEntry 16 }

fgs2528kxPortTrafficRxQ1 OBJECT-TYPE
   SYNTAX      Counter64
   MAX-ACCESS  read-only
   STATUS      current
   DESCRIPTION
       " "
   ::= { fgs2528kxPortTrafficStatisticsEntry 17 }

fgs2528kxPortTrafficRxQ2 OBJECT-TYPE
   SYNTAX      Counter64
   MAX-ACCESS  read-only
   STATUS      current
   DESCRIPTION
       " "
   ::= { fgs2528kxPortTrafficStatisticsEntry 18 }

fgs2528kxPortTrafficRxQ3 OBJECT-TYPE
   SYNTAX      Counter64
   MAX-ACCESS  read-only
   STATUS      current
   DESCRIPTION
       " "
   ::= { fgs2528kxPortTrafficStatisticsEntry 19 }

fgs2528kxPortTrafficRxQ4 OBJECT-TYPE
   SYNTAX      Counter64
   MAX-ACCESS  read-only
   STATUS      current
   DESCRIPTION
       " "
   ::= { fgs2528kxPortTrafficStatisticsEntry 20 }

fgs2528kxPortTrafficRxQ5 OBJECT-TYPE
   SYNTAX      Counter64
   MAX-ACCESS  read-only
   STATUS      current
   DESCRIPTION
       " "
   ::= { fgs2528kxPortTrafficStatisticsEntry 21 }

fgs2528kxPortTrafficRxQ6 OBJECT-TYPE
   SYNTAX      Counter64
   MAX-ACCESS  read-only
   STATUS      current
   DESCRIPTION
       " "
   ::= { fgs2528kxPortTrafficStatisticsEntry 22 }

fgs2528kxPortTrafficRxQ7 OBJECT-TYPE
   SYNTAX      Counter64
   MAX-ACCESS  read-only
   STATUS      current
   DESCRIPTION
       " "
   ::= { fgs2528kxPortTrafficStatisticsEntry 23 }

fgs2528kxPortTrafficRxDrops OBJECT-TYPE
   SYNTAX      Counter64
   MAX-ACCESS  read-only
   STATUS      current
   DESCRIPTION
       " "
   ::= { fgs2528kxPortTrafficStatisticsEntry 24 }

fgs2528kxPortTrafficRxCRCorAlignment OBJECT-TYPE
   SYNTAX      Counter64
   MAX-ACCESS  read-only
   STATUS      current
   DESCRIPTION
       " "
   ::= { fgs2528kxPortTrafficStatisticsEntry 25 }

fgs2528kxPortTrafficRxUndersize OBJECT-TYPE
   SYNTAX      Counter64
   MAX-ACCESS  read-only
   STATUS      current
   DESCRIPTION
       " "
   ::= { fgs2528kxPortTrafficStatisticsEntry 26 }

fgs2528kxPortTrafficRxOversize OBJECT-TYPE
   SYNTAX      Counter64
   MAX-ACCESS  read-only
   STATUS      current
   DESCRIPTION
       " "
   ::= { fgs2528kxPortTrafficStatisticsEntry 27 }

fgs2528kxPortTrafficRxFragments OBJECT-TYPE
   SYNTAX      Counter64
   MAX-ACCESS  read-only
   STATUS      current
   DESCRIPTION
       " "
   ::= { fgs2528kxPortTrafficStatisticsEntry 28 }

fgs2528kxPortTrafficRxJabber OBJECT-TYPE
   SYNTAX      Counter64
   MAX-ACCESS  read-only
   STATUS      current
   DESCRIPTION
       " "
   ::= { fgs2528kxPortTrafficStatisticsEntry 29 }

fgs2528kxPortTrafficRxFiltered OBJECT-TYPE
   SYNTAX      Counter64
   MAX-ACCESS  read-only
   STATUS      current
   DESCRIPTION
       " "
   ::= { fgs2528kxPortTrafficStatisticsEntry 30 }

fgs2528kxPortTrafficTxPackets OBJECT-TYPE
   SYNTAX      Counter64
   MAX-ACCESS  read-only
   STATUS      current
   DESCRIPTION
       " "
   ::= { fgs2528kxPortTrafficStatisticsEntry 31 }

fgs2528kxPortTrafficTxOctets OBJECT-TYPE
   SYNTAX      Counter64
   MAX-ACCESS  read-only
   STATUS      current
   DESCRIPTION
       " "
   ::= { fgs2528kxPortTrafficStatisticsEntry 32 }

fgs2528kxPortTrafficTxUnicast OBJECT-TYPE
   SYNTAX      Counter64
   MAX-ACCESS  read-only
   STATUS      current
   DESCRIPTION
       " "
   ::= { fgs2528kxPortTrafficStatisticsEntry 33 }

fgs2528kxPortTrafficTxMulticast OBJECT-TYPE
   SYNTAX      Counter64
   MAX-ACCESS  read-only
   STATUS      current
   DESCRIPTION
       " "
   ::= { fgs2528kxPortTrafficStatisticsEntry 34 }

fgs2528kxPortTrafficTxBroadcast OBJECT-TYPE
   SYNTAX      Counter64
   MAX-ACCESS  read-only
   STATUS      current
   DESCRIPTION
       " "
   ::= { fgs2528kxPortTrafficStatisticsEntry 35 }

fgs2528kxPortTrafficTxPause OBJECT-TYPE
   SYNTAX      Counter64
   MAX-ACCESS  read-only
   STATUS      current
   DESCRIPTION
       " "
   ::= { fgs2528kxPortTrafficStatisticsEntry 36 }

fgs2528kxPortTrafficTx64Bytes OBJECT-TYPE
   SYNTAX      Counter64
   MAX-ACCESS  read-only
   STATUS      current
   DESCRIPTION
       " "
   ::= { fgs2528kxPortTrafficStatisticsEntry 37 }

fgs2528kxPortTrafficTx65to127Bytes OBJECT-TYPE
   SYNTAX      Counter64
   MAX-ACCESS  read-only
   STATUS      current
   DESCRIPTION
       " "
   ::= { fgs2528kxPortTrafficStatisticsEntry 38 }

fgs2528kxPortTrafficTx128to255Bytes OBJECT-TYPE
   SYNTAX      Counter64
   MAX-ACCESS  read-only
   STATUS      current
   DESCRIPTION
       " "
   ::= { fgs2528kxPortTrafficStatisticsEntry 39 }

fgs2528kxPortTrafficTx256to511Bytes OBJECT-TYPE
   SYNTAX      Counter64
   MAX-ACCESS  read-only
   STATUS      current
   DESCRIPTION
       " "
   ::= { fgs2528kxPortTrafficStatisticsEntry 40 }

fgs2528kxPortTrafficTx512to1023Bytes OBJECT-TYPE
   SYNTAX      Counter64
   MAX-ACCESS  read-only
   STATUS      current
   DESCRIPTION
       " "
   ::= { fgs2528kxPortTrafficStatisticsEntry 41 }

fgs2528kxPortTrafficTx1024to1526Bytes OBJECT-TYPE
   SYNTAX      Counter64
   MAX-ACCESS  read-only
   STATUS      current
   DESCRIPTION
       " "
   ::= { fgs2528kxPortTrafficStatisticsEntry 42 }

fgs2528kxPortTrafficTxExceecd1527Bytes OBJECT-TYPE
   SYNTAX      Counter64
   MAX-ACCESS  read-only
   STATUS      current
   DESCRIPTION
       " "
   ::= { fgs2528kxPortTrafficStatisticsEntry 43 }

fgs2528kxPortTrafficTxQ0 OBJECT-TYPE
   SYNTAX      Counter64
   MAX-ACCESS  read-only
   STATUS      current
   DESCRIPTION
       " "
   ::= { fgs2528kxPortTrafficStatisticsEntry 44 }

fgs2528kxPortTrafficTxQ1 OBJECT-TYPE
   SYNTAX      Counter64
   MAX-ACCESS  read-only
   STATUS      current
   DESCRIPTION
       " "
   ::= { fgs2528kxPortTrafficStatisticsEntry 45 }

fgs2528kxPortTrafficTxQ2 OBJECT-TYPE
   SYNTAX      Counter64
   MAX-ACCESS  read-only
   STATUS      current
   DESCRIPTION
       " "
   ::= { fgs2528kxPortTrafficStatisticsEntry 46 }

fgs2528kxPortTrafficTxQ3 OBJECT-TYPE
   SYNTAX      Counter64
   MAX-ACCESS  read-only
   STATUS      current
   DESCRIPTION
       " "
   ::= { fgs2528kxPortTrafficStatisticsEntry 47 }

fgs2528kxPortTrafficTxQ4 OBJECT-TYPE
   SYNTAX      Counter64
   MAX-ACCESS  read-only
   STATUS      current
   DESCRIPTION
       " "
   ::= { fgs2528kxPortTrafficStatisticsEntry 48 }

fgs2528kxPortTrafficTxQ5 OBJECT-TYPE
   SYNTAX      Counter64
   MAX-ACCESS  read-only
   STATUS      current
   DESCRIPTION
       " "
   ::= { fgs2528kxPortTrafficStatisticsEntry 49 }

fgs2528kxPortTrafficTxQ6 OBJECT-TYPE
   SYNTAX      Counter64
   MAX-ACCESS  read-only
   STATUS      current
   DESCRIPTION
       " "
   ::= { fgs2528kxPortTrafficStatisticsEntry 50 }


fgs2528kxPortTrafficTxQ7 OBJECT-TYPE
   SYNTAX      Counter64
   MAX-ACCESS  read-only
   STATUS      current
   DESCRIPTION
       " "
   ::= { fgs2528kxPortTrafficStatisticsEntry 51 }

fgs2528kxPortTrafficTxDrops OBJECT-TYPE
   SYNTAX      Counter64
   MAX-ACCESS  read-only
   STATUS      current
   DESCRIPTION
       " "
   ::= { fgs2528kxPortTrafficStatisticsEntry 52 }

fgs2528kxPortTrafficTxLateOrExcColl OBJECT-TYPE
   SYNTAX      Counter64
   MAX-ACCESS  read-only
   STATUS      current
   DESCRIPTION
       " "
   ::= { fgs2528kxPortTrafficStatisticsEntry 53 }


fgs2528kxPortQoSStatistics                                     OBJECT IDENTIFIER ::= { fgs2528kxPort 3 }

fgs2528kxPortQoSStatisticsClear OBJECT-TYPE
   SYNTAX      INTEGER(0|1)
   MAX-ACCESS  read-only
   STATUS      current
   DESCRIPTION
       "default: 0
       0: none
       1: clear "
   ::= { fgs2528kxPortQoSStatistics 1 }

fgs2528kxPortQoSStatisticsTable OBJECT-TYPE
   SYNTAX      SEQUENCE OF FGS2528KXPortQoSStatisticsEntry
   MAX-ACCESS  not-accessible
   STATUS      current
   DESCRIPTION
       " "
   ::= { fgs2528kxPortQoSStatistics 2 }

fgs2528kxPortQoSStatisticsEntry OBJECT-TYPE
   SYNTAX      FGS2528KXPortQoSStatisticsEntry
   MAX-ACCESS  not-accessible
   STATUS      current
   DESCRIPTION
       ""
   INDEX    { fgs2528kxPortQoSStatisticsPort  }
   ::= { fgs2528kxPortQoSStatisticsTable 1 }

FGS2528KXPortQoSStatisticsEntry ::= SEQUENCE {
   fgs2528kxPortQoSStatisticsPort   INTEGER,
   fgs2528kxPortQoSQ0Rx	            Counter64,
   fgs2528kxPortQoSQ0Tx	            Counter64,
   fgs2528kxPortQoSQ1Rx	            Counter64,
   fgs2528kxPortQoSQ1Tx	            Counter64,
   fgs2528kxPortQoSQ2Rx	            Counter64,
   fgs2528kxPortQoSQ2Tx	            Counter64,
   fgs2528kxPortQoSQ3Rx	            Counter64,
   fgs2528kxPortQoSQ3Tx	            Counter64,
   fgs2528kxPortQoSQ4Rx	            Counter64,
   fgs2528kxPortQoSQ4Tx	            Counter64,
   fgs2528kxPortQoSQ5Rx	            Counter64,
   fgs2528kxPortQoSQ5Tx	            Counter64,
   fgs2528kxPortQoSQ6Rx	            Counter64,
   fgs2528kxPortQoSQ6Tx	            Counter64,
   fgs2528kxPortQoSQ7Rx	            Counter64,
   fgs2528kxPortQoSQ7Tx	            Counter64
}

fgs2528kxPortQoSStatisticsPort OBJECT-TYPE
   SYNTAX      INTEGER (1..4095)
   MAX-ACCESS  not-accessible
   STATUS      current
   DESCRIPTION
       " "
   ::= { fgs2528kxPortQoSStatisticsEntry 1 }

fgs2528kxPortQoSQ0Rx OBJECT-TYPE
   SYNTAX      Counter64
   MAX-ACCESS  read-only
   STATUS      current
   DESCRIPTION
       " "
   ::= { fgs2528kxPortQoSStatisticsEntry 2 }

fgs2528kxPortQoSQ0Tx OBJECT-TYPE
   SYNTAX      Counter64
   MAX-ACCESS  read-only
   STATUS      current
   DESCRIPTION
       " "
   ::= { fgs2528kxPortQoSStatisticsEntry 3 }

fgs2528kxPortQoSQ1Rx OBJECT-TYPE
   SYNTAX      Counter64
   MAX-ACCESS  read-only
   STATUS      current
   DESCRIPTION
       " "
   ::= { fgs2528kxPortQoSStatisticsEntry 4 }

fgs2528kxPortQoSQ1Tx OBJECT-TYPE
   SYNTAX      Counter64
   MAX-ACCESS  read-only
   STATUS      current
   DESCRIPTION
       " "
   ::= { fgs2528kxPortQoSStatisticsEntry 5 }

fgs2528kxPortQoSQ2Rx OBJECT-TYPE
   SYNTAX      Counter64
   MAX-ACCESS  read-only
   STATUS      current
   DESCRIPTION
       " "
   ::= { fgs2528kxPortQoSStatisticsEntry 6 }

fgs2528kxPortQoSQ2Tx OBJECT-TYPE
   SYNTAX      Counter64
   MAX-ACCESS  read-only
   STATUS      current
   DESCRIPTION
       " "
   ::= { fgs2528kxPortQoSStatisticsEntry 7 }

fgs2528kxPortQoSQ3Rx OBJECT-TYPE
   SYNTAX      Counter64
   MAX-ACCESS  read-only
   STATUS      current
   DESCRIPTION
       " "
   ::= { fgs2528kxPortQoSStatisticsEntry 8 }

fgs2528kxPortQoSQ3Tx OBJECT-TYPE
   SYNTAX      Counter64
   MAX-ACCESS  read-only
   STATUS      current
   DESCRIPTION
       " "
   ::= { fgs2528kxPortQoSStatisticsEntry 9 }

fgs2528kxPortQoSQ4Rx OBJECT-TYPE
   SYNTAX      Counter64
   MAX-ACCESS  read-only
   STATUS      current
   DESCRIPTION
       " "
   ::= { fgs2528kxPortQoSStatisticsEntry 10 }

fgs2528kxPortQoSQ4Tx OBJECT-TYPE
   SYNTAX      Counter64
   MAX-ACCESS  read-only
   STATUS      current
   DESCRIPTION
       " "
   ::= { fgs2528kxPortQoSStatisticsEntry 11 }

fgs2528kxPortQoSQ5Rx OBJECT-TYPE
   SYNTAX      Counter64
   MAX-ACCESS  read-only
   STATUS      current
   DESCRIPTION
       " "
   ::= { fgs2528kxPortQoSStatisticsEntry 12 }

fgs2528kxPortQoSQ5Tx OBJECT-TYPE
   SYNTAX      Counter64
   MAX-ACCESS  read-only
   STATUS      current
   DESCRIPTION
       " "
   ::= { fgs2528kxPortQoSStatisticsEntry 13 }

fgs2528kxPortQoSQ6Rx OBJECT-TYPE
   SYNTAX      Counter64
   MAX-ACCESS  read-only
   STATUS      current
   DESCRIPTION
       " "
   ::= { fgs2528kxPortQoSStatisticsEntry 14 }

fgs2528kxPortQoSQ6Tx OBJECT-TYPE
   SYNTAX      Counter64
   MAX-ACCESS  read-only
   STATUS      current
   DESCRIPTION
       " "
   ::= { fgs2528kxPortQoSStatisticsEntry 15 }

fgs2528kxPortQoSQ7Rx OBJECT-TYPE
   SYNTAX      Counter64
   MAX-ACCESS  read-only
   STATUS      current
   DESCRIPTION
       " "
   ::= { fgs2528kxPortQoSStatisticsEntry 16 }

fgs2528kxPortQoSQ7Tx OBJECT-TYPE
   SYNTAX      Counter64
   MAX-ACCESS  read-only
   STATUS      current
   DESCRIPTION
       " "
   ::= { fgs2528kxPortQoSStatisticsEntry 17 }

fgs2528kxSFPInfoTable OBJECT-TYPE
   SYNTAX      SEQUENCE OF FGS2528KXSFPInfoEntry
   MAX-ACCESS  not-accessible
   STATUS      current
   DESCRIPTION
       " "
   ::= { fgs2528kxPort 4 }

fgs2528kxSFPInfoEntry OBJECT-TYPE
   SYNTAX      FGS2528KXSFPInfoEntry
   MAX-ACCESS  not-accessible
   STATUS      current
   DESCRIPTION
       ""
   INDEX    { fgs2528kxSFPInfoIndex }
   ::= { fgs2528kxSFPInfoTable 1 }

FGS2528KXSFPInfoEntry ::= SEQUENCE {
   fgs2528kxSFPInfoIndex               INTEGER,
   fgs2528kxSFPInfoPort                DisplayString,
   fgs2528kxSFPConnectorType           DisplayString,
   fgs2528kxSFPFiberType               DisplayString,
   fgs2528kxSFPTxCentralWavelength     DisplayString,
   fgs2528kxSFPBaudRate                DisplayString,
   fgs2528kxSFPVendorOUI               DisplayString,
   fgs2528kxSFPVendorName              DisplayString,
   fgs2528kxSFPVendorPN                DisplayString,
   fgs2528kxSFPVendorRev               DisplayString,
   fgs2528kxSFPVendorSN                DisplayString,
   fgs2528kxSFPDateCode                DisplayString,
   fgs2528kxSFPTemperature             DisplayString,
   fgs2528kxSFPVcc                     DisplayString,
   fgs2528kxSFPMon1Bias                DisplayString,
   fgs2528kxSFPMon2TxPWR               DisplayString,
   fgs2528kxSFPMon3RxPWR               DisplayString
}

fgs2528kxSFPInfoIndex OBJECT-TYPE
   SYNTAX      INTEGER (1..4095)
   MAX-ACCESS  not-accessible
   STATUS      current
   DESCRIPTION
       " "
   ::= { fgs2528kxSFPInfoEntry 1 }

fgs2528kxSFPInfoPort OBJECT-TYPE
   SYNTAX      DisplayString
   MAX-ACCESS  read-only
   STATUS      current
   DESCRIPTION
       " "
   ::= { fgs2528kxSFPInfoEntry 2 }

fgs2528kxSFPConnectorType OBJECT-TYPE
   SYNTAX      DisplayString
   MAX-ACCESS  read-only
   STATUS      current
   DESCRIPTION
       " "
   ::= { fgs2528kxSFPInfoEntry 3 }

fgs2528kxSFPFiberType OBJECT-TYPE
   SYNTAX      DisplayString
   MAX-ACCESS  read-only
   STATUS      current
   DESCRIPTION
       " "
   ::= { fgs2528kxSFPInfoEntry 4 }

fgs2528kxSFPTxCentralWavelength OBJECT-TYPE
   SYNTAX      DisplayString
   MAX-ACCESS  read-only
   STATUS      current
   DESCRIPTION
       " "
   ::= { fgs2528kxSFPInfoEntry 5 }

fgs2528kxSFPBaudRate OBJECT-TYPE
   SYNTAX      DisplayString
   MAX-ACCESS  read-only
   STATUS      current
   DESCRIPTION
       " "
   ::= { fgs2528kxSFPInfoEntry 6 }

fgs2528kxSFPVendorOUI OBJECT-TYPE
   SYNTAX      DisplayString
   MAX-ACCESS  read-only
   STATUS      current
   DESCRIPTION
       " "
   ::= { fgs2528kxSFPInfoEntry 7 }

fgs2528kxSFPVendorName OBJECT-TYPE
   SYNTAX      DisplayString
   MAX-ACCESS  read-only
   STATUS      current
   DESCRIPTION
       " "
   ::= { fgs2528kxSFPInfoEntry 8 }

fgs2528kxSFPVendorPN OBJECT-TYPE
   SYNTAX      DisplayString
   MAX-ACCESS  read-only
   STATUS      current
   DESCRIPTION
       " "
   ::= { fgs2528kxSFPInfoEntry 9 }

fgs2528kxSFPVendorRev OBJECT-TYPE
   SYNTAX      DisplayString
   MAX-ACCESS  read-only
   STATUS      current
   DESCRIPTION
       " "
   ::= { fgs2528kxSFPInfoEntry 10 }

fgs2528kxSFPVendorSN OBJECT-TYPE
   SYNTAX      DisplayString
   MAX-ACCESS  read-only
   STATUS      current
   DESCRIPTION
       " "
   ::= { fgs2528kxSFPInfoEntry 11 }

fgs2528kxSFPDateCode OBJECT-TYPE
   SYNTAX      DisplayString
   MAX-ACCESS  read-only
   STATUS      current
   DESCRIPTION
       " "
   ::= { fgs2528kxSFPInfoEntry 12 }

fgs2528kxSFPTemperature OBJECT-TYPE
   SYNTAX      DisplayString
   MAX-ACCESS  read-only
   STATUS      current
   DESCRIPTION
       " "
   ::= { fgs2528kxSFPInfoEntry 13 }

fgs2528kxSFPVcc OBJECT-TYPE
   SYNTAX      DisplayString
   MAX-ACCESS  read-only
   STATUS      current
   DESCRIPTION
       " "
   ::= { fgs2528kxSFPInfoEntry 14 }

fgs2528kxSFPMon1Bias OBJECT-TYPE
   SYNTAX      DisplayString
   MAX-ACCESS  read-only
   STATUS      current
   DESCRIPTION
       " "
   ::= { fgs2528kxSFPInfoEntry 15 }

fgs2528kxSFPMon2TxPWR OBJECT-TYPE
   SYNTAX      DisplayString
   MAX-ACCESS  read-only
   STATUS      current
   DESCRIPTION
       " "
   ::= { fgs2528kxSFPInfoEntry 16 }

fgs2528kxSFPMon3RxPWR OBJECT-TYPE
   SYNTAX      DisplayString
   MAX-ACCESS  read-only
   STATUS      current
   DESCRIPTION
       " "
   ::= { fgs2528kxSFPInfoEntry 17 }


fgs2528kxGARP                                                   OBJECT IDENTIFIER ::= { fgs2528kxConfiguration 3 }

fgs2528kxGARPConfTable OBJECT-TYPE
   SYNTAX      SEQUENCE OF FGS2528KXGARPConfEntry
   MAX-ACCESS  not-accessible
   STATUS      current
   DESCRIPTION
       " "
   ::= { fgs2528kxGARP 1 }

fgs2528kxGARPConfEntry OBJECT-TYPE
   SYNTAX      FGS2528KXGARPConfEntry
   MAX-ACCESS  not-accessible
   STATUS      current
   DESCRIPTION
       ""
   INDEX    { fgs2528kxGARPConfPort  }
   ::= { fgs2528kxGARPConfTable 1 }

FGS2528KXGARPConfEntry ::= SEQUENCE {
   fgs2528kxGARPConfPort           INTEGER,
   fgs2528kxGARPJoinTimer          INTEGER,
   fgs2528kxGARPLeaveTimer         INTEGER,
   fgs2528kxGARPLeaveAllTimer      INTEGER,
   fgs2528kxGARPApplicantion       INTEGER,
   fgs2528kxGARPAttributeType      INTEGER,
   fgs2528kxGARPApplicant          INTEGER
}

fgs2528kxGARPConfPort OBJECT-TYPE
   SYNTAX      INTEGER (1..4095)
   MAX-ACCESS  not-accessible
   STATUS      current
   DESCRIPTION
       " "
   ::= { fgs2528kxGARPConfEntry 1 }

fgs2528kxGARPJoinTimer OBJECT-TYPE
   SYNTAX      INTEGER (200..1000)
   MAX-ACCESS  read-write
   STATUS      current
   DESCRIPTION
       "default: 200, range : 200 - 1000 "
   ::= { fgs2528kxGARPConfEntry 2 }

fgs2528kxGARPLeaveTimer OBJECT-TYPE
   SYNTAX      INTEGER (600..3000)
   MAX-ACCESS  read-write
   STATUS      current
   DESCRIPTION
       "default: 600 , range : 600 - 3000"
   ::= { fgs2528kxGARPConfEntry 3 }

fgs2528kxGARPLeaveAllTimer OBJECT-TYPE
   SYNTAX      INTEGER (10000..50000)
   MAX-ACCESS  read-write
   STATUS      current
   DESCRIPTION
       "default: 10000, range : 10000 - 50000 "
   ::= { fgs2528kxGARPConfEntry 4 }

fgs2528kxGARPApplicantion OBJECT-TYPE
   SYNTAX      INTEGER(1)
   MAX-ACCESS  read-write
   STATUS      current
   DESCRIPTION
       "default: 1
       1: GVRP"
   ::= { fgs2528kxGARPConfEntry 5 }

fgs2528kxGARPAttributeType OBJECT-TYPE
   SYNTAX      INTEGER(1)
   MAX-ACCESS  read-write
   STATUS      current
   DESCRIPTION
       "default: 1
       1: VLAN"
   ::= { fgs2528kxGARPConfEntry 6 }

fgs2528kxGARPApplicant OBJECT-TYPE
   SYNTAX      INTEGER(0|1)
   MAX-ACCESS  read-write
   STATUS      current
   DESCRIPTION
       "default: 0
       0: normal-participant
       1: non-participant"
   ::= { fgs2528kxGARPConfEntry 7 }

fgs2528kxGARPStatisticsTable OBJECT-TYPE
   SYNTAX      SEQUENCE OF FGS2528KXGARPStatisticsEntry
   MAX-ACCESS  not-accessible
   STATUS      current
   DESCRIPTION
       " Show the basic GARP port statistics. "
   ::= { fgs2528kxGARP 2 }

fgs2528kxGARPStatisticsEntry OBJECT-TYPE
   SYNTAX      FGS2528KXGARPStatisticsEntry
   MAX-ACCESS  not-accessible
   STATUS      current
   DESCRIPTION
       ""
   INDEX    { fgs2528kxGARPStatisticsPort  }
   ::= { fgs2528kxGARPStatisticsTable 1 }

FGS2528KXGARPStatisticsEntry ::= SEQUENCE {
   fgs2528kxGARPStatisticsPort             INTEGER,
   fgs2528kxGARPStatisticsPeerMAC          DisplayString,
   fgs2528kxGARPStatisticsFailedCount      Counter32
}

fgs2528kxGARPStatisticsPort OBJECT-TYPE
   SYNTAX      INTEGER (1..4095)
   MAX-ACCESS  not-accessible
   STATUS      current
   DESCRIPTION
       " port, range : 1 - port number. "
   ::= { fgs2528kxGARPStatisticsEntry 1 }

fgs2528kxGARPStatisticsPeerMAC OBJECT-TYPE
   SYNTAX      DisplayString
   MAX-ACCESS  read-only
   STATUS      current
   DESCRIPTION
       " Peer MAC is MAC address of the neighbour Switch from with GARP frame is received.  "
   ::= { fgs2528kxGARPStatisticsEntry 2 }

fgs2528kxGARPStatisticsFailedCount OBJECT-TYPE
   SYNTAX      Counter32
   MAX-ACCESS  read-only
   STATUS      current
   DESCRIPTION
       " explain Failed count here. "
   ::= { fgs2528kxGARPStatisticsEntry 3 }

fgs2528kxGVRP                                                   OBJECT IDENTIFIER ::= { fgs2528kxConfiguration 4 }

fgs2528kxGVRPConf                                                   OBJECT IDENTIFIER ::= { fgs2528kxGVRP 1 }

fgs2528kxGVRPMode OBJECT-TYPE
   SYNTAX      INTEGER(0|1)
   MAX-ACCESS  read-write
   STATUS      current
   DESCRIPTION
       "default: 0,
        0: disable,
        1: enable. "
   ::= { fgs2528kxGVRPConf 1 }

fgs2528kxGVRPConfTable OBJECT-TYPE
   SYNTAX      SEQUENCE OF FGS2528KXGVRPConfEntry
   MAX-ACCESS  not-accessible
   STATUS      current
   DESCRIPTION
       " "
   ::= { fgs2528kxGVRPConf 2 }

fgs2528kxGVRPConfEntry OBJECT-TYPE
   SYNTAX      FGS2528KXGVRPConfEntry
   MAX-ACCESS  not-accessible
   STATUS      current
   DESCRIPTION
       ""
   INDEX    { fgs2528kxGVRPConfPort  }
   ::= { fgs2528kxGVRPConfTable 1 }

FGS2528KXGVRPConfEntry ::= SEQUENCE {
   fgs2528kxGVRPConfPort        INTEGER,
   fgs2528kxGVRPConfPortMode	INTEGER,
   fgs2528kxGVRPConfPortRRole	INTEGER
}

fgs2528kxGVRPConfPort OBJECT-TYPE
   SYNTAX      INTEGER (1..4095)
   MAX-ACCESS  not-accessible
   STATUS      current
   DESCRIPTION
       " "
   ::= { fgs2528kxGVRPConfEntry 1 }

fgs2528kxGVRPConfPortMode OBJECT-TYPE
   SYNTAX      INTEGER(0|1)
   MAX-ACCESS  read-write
   STATUS      current
   DESCRIPTION
       "default: 0
       1: enable
       0: disable"
   ::= { fgs2528kxGVRPConfEntry 2 }

fgs2528kxGVRPConfPortRRole OBJECT-TYPE
   SYNTAX      INTEGER(0|1)
   MAX-ACCESS  read-write
   STATUS      current
   DESCRIPTION
       "default: 0
       1: enable
       0: disable"
   ::= { fgs2528kxGVRPConfEntry 3 }

fgs2528kxGVRPStatisticsTable OBJECT-TYPE
   SYNTAX      SEQUENCE OF FGS2528KXGVRPStatisticsEntry
   MAX-ACCESS  not-accessible
   STATUS      current
   DESCRIPTION
       " "
   ::= { fgs2528kxGVRP 2 }

fgs2528kxGVRPStatisticsEntry OBJECT-TYPE
   SYNTAX      FGS2528KXGVRPStatisticsEntry
   MAX-ACCESS  not-accessible
   STATUS      current
   DESCRIPTION
       ""
   INDEX    { fgs2528kxGVRPStatisticsPort  }
   ::= { fgs2528kxGVRPStatisticsTable 1 }

FGS2528KXGVRPStatisticsEntry ::= SEQUENCE {
   fgs2528kxGVRPStatisticsPort         INTEGER,
   fgs2528kxGVRPStatisticsJoinTxCnt    Counter32,
   fgs2528kxGVRPStatisticsLeaveTxCnt   Counter32
}

fgs2528kxGVRPStatisticsPort OBJECT-TYPE
   SYNTAX      INTEGER (1..4095)
   MAX-ACCESS  not-accessible
   STATUS      current
   DESCRIPTION
       " "
   ::= { fgs2528kxGVRPStatisticsEntry 1 }

fgs2528kxGVRPStatisticsJoinTxCnt OBJECT-TYPE
   SYNTAX      Counter32
   MAX-ACCESS  read-only
   STATUS      current
   DESCRIPTION
       ""
   ::= { fgs2528kxGVRPStatisticsEntry 2 }

fgs2528kxGVRPStatisticsLeaveTxCnt OBJECT-TYPE
   SYNTAX      Counter32
   MAX-ACCESS  read-only
   STATUS      current
   DESCRIPTION
       ""
   ::= { fgs2528kxGVRPStatisticsEntry 3 }

fgs2528kxThermalProtection                                     OBJECT IDENTIFIER ::= { fgs2528kxConfiguration 5 }

fgs2528kxPriority0Temperature OBJECT-TYPE
   SYNTAX      INTEGER(0..255)
   MAX-ACCESS  read-write
   STATUS      current
   DESCRIPTION
       "default: 255, range : 0 - 255 "
   ::= { fgs2528kxThermalProtection 1 }

fgs2528kxPriority1Temperature OBJECT-TYPE
   SYNTAX      INTEGER(0..255)
   MAX-ACCESS  read-write
   STATUS      current
   DESCRIPTION
       "default: 255, range : 0 - 255 "
   ::= { fgs2528kxThermalProtection 2 }

fgs2528kxPriority2Temperature OBJECT-TYPE
   SYNTAX      INTEGER(0..255)
   MAX-ACCESS  read-write
   STATUS      current
   DESCRIPTION
       "default: 255, range : 0 - 255 "
   ::= { fgs2528kxThermalProtection 3 }

fgs2528kxPriority3Temperature OBJECT-TYPE
   SYNTAX      INTEGER(0..255)
   MAX-ACCESS  read-write
   STATUS      current
   DESCRIPTION
       "default: 255, range : 0 - 255 "
   ::= { fgs2528kxThermalProtection 4 }

fgs2528kxThermalProtectionTable OBJECT-TYPE
   SYNTAX      SEQUENCE OF FGS2528KXThermalProtectionEntry
   MAX-ACCESS  not-accessible
   STATUS      current
   DESCRIPTION
       " "
   ::= { fgs2528kxThermalProtection 5 }

fgs2528kxThermalProtectionEntry OBJECT-TYPE
   SYNTAX      FGS2528KXThermalProtectionEntry
   MAX-ACCESS  not-accessible
   STATUS      current
   DESCRIPTION
       ""
   INDEX    { fgs2528kxThermalProtectionPort  }
   ::= { fgs2528kxThermalProtectionTable 1 }

FGS2528KXThermalProtectionEntry ::= SEQUENCE {
   fgs2528kxThermalProtectionPort              INTEGER,
   fgs2528kxThermalProtectionPortTemperature   INTEGER,
   fgs2528kxThermalProtectionPortPriority      INTEGER,
   fgs2528kxThermalProtectionPortStatus        DisplayString
}

fgs2528kxThermalProtectionPort OBJECT-TYPE
   SYNTAX      INTEGER (1..4095)
   MAX-ACCESS  not-accessible
   STATUS      current
   DESCRIPTION
       " "
   ::= { fgs2528kxThermalProtectionEntry 1 }

fgs2528kxThermalProtectionPortTemperature OBJECT-TYPE
   SYNTAX      INTEGER(0..255)
   MAX-ACCESS  read-only
   STATUS      current
   DESCRIPTION
       ""
   ::= { fgs2528kxThermalProtectionEntry 2 }

fgs2528kxThermalProtectionPortPriority OBJECT-TYPE
   SYNTAX      INTEGER(0..3)
   MAX-ACCESS  read-write
   STATUS      current
   DESCRIPTION
       "default: 0, range : 0 - 3"
   ::= { fgs2528kxThermalProtectionEntry 3 }

fgs2528kxThermalProtectionPortStatus OBJECT-TYPE
   SYNTAX      DisplayString
   MAX-ACCESS  read-only
   STATUS      current
   DESCRIPTION
       ""
   ::= { fgs2528kxThermalProtectionEntry 4 }


fgs2528kxMirroring                                             OBJECT IDENTIFIER ::= { fgs2528kxConfiguration 6 }

fgs2528kxPortToMirrorOn OBJECT-TYPE
   SYNTAX      INTEGER(0..10)
   MAX-ACCESS  read-write
   STATUS      current
   DESCRIPTION
       "default: 0
        0: disable,
        range : 1 - port number. "
   ::= { fgs2528kxMirroring 1 }

fgs2528kxMirrorTable OBJECT-TYPE
   SYNTAX      SEQUENCE OF FGS2528KXMirrorEntry
   MAX-ACCESS  not-accessible
   STATUS      current
   DESCRIPTION
       " "
   ::= { fgs2528kxMirroring 2 }

fgs2528kxMirrorEntry OBJECT-TYPE
   SYNTAX      FGS2528KXMirrorEntry
   MAX-ACCESS  not-accessible
   STATUS      current
   DESCRIPTION
       ""
   INDEX    { fgs2528kxMirrorPort  }
   ::= { fgs2528kxMirrorTable 1 }

FGS2528KXMirrorEntry ::= SEQUENCE {
   fgs2528kxMirrorPort		INTEGER,
   fgs2528kxMirrorMode		INTEGER
}

fgs2528kxMirrorPort OBJECT-TYPE
   SYNTAX      INTEGER (1..4095)
   MAX-ACCESS  not-accessible
   STATUS      current
   DESCRIPTION
       " "
   ::= { fgs2528kxMirrorEntry 1 }

fgs2528kxMirrorMode OBJECT-TYPE
   SYNTAX      INTEGER(0..3)
   MAX-ACCESS  read-write
   STATUS      current
   DESCRIPTION
       "default: 0
       0: disable
       1: enable
       2: rx only
       3: tx only
       Setting Tx mirroring for analyzer port has no effect. Tx mirroring ignored"
   ::= { fgs2528kxMirrorEntry 2 }

fgs2528kxTrapEventSeverity                                             OBJECT IDENTIFIER ::= { fgs2528kxConfiguration 7 }

fgs2528kxTrapEventSeverityACL OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 1 }

fgs2528kxTrapEventSeverityACLLog OBJECT-TYPE
   SYNTAX      INTEGER (0..7)
   MAX-ACCESS  read-write
   STATUS      current
   DESCRIPTION
       " default:  7(Debug)
        0: Emergency
        1: Alert
        2: Critical
        3: Error
        4: Warning
        5: Notice
        6: Info
        7: Debug"
   ::= { fgs2528kxTrapEventSeverity 2 }

fgs2528kxTrapEventSeverityAccessMgmt OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 3 }

fgs2528kxTrapEventSeverityAuthFailed OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { fgs2528kxTrapEventSeverity 4 }

fgs2528kxTrapEventSeverityColdStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { fgs2528kxTrapEventSeverity 5 }

fgs2528kxTrapEventSeverityConfigInfo OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 6 }

fgs2528kxTrapEventSeverityFirmwareUpgrade OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 7 }

fgs2528kxTrapEventSeverityImportExport OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 8 }

fgs2528kxTrapEventSeverityLACP OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 9 }

fgs2528kxTrapEventSeverityLinkStatus OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { fgs2528kxTrapEventSeverity 10 }

fgs2528kxTrapEventSeverityLogin OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 11 }

fgs2528kxTrapEventSeverityLogout OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 12 }

fgs2528kxTrapEventSeverityLoopProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 13 }

fgs2528kxTrapEventSeverityMgmtIPChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 14 }

fgs2528kxTrapEventSeverityModuleChange OBJECT-TYPE
   SYNTAX      INTEGER (0..7)
   MAX-ACCESS  read-write
   STATUS      current
   DESCRIPTION
       " default:  5(Notice)
        0: Emergency
        1: Alert
        2: Critical
        3: Error
        4: Warning
        5: Notice
        6: Info
        7: Debug"
   ::= { fgs2528kxTrapEventSeverity 15 }

fgs2528kxTrapEventSeverityNAS OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 16 }

fgs2528kxTrapEventSeverityPasswdChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 17 }

fgs2528kxTrapEventSeverityPortSecurity OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 18 }

fgs2528kxTrapEventSeverityThermalProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 19 }

fgs2528kxTrapEventSeverityVLAN OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { fgs2528kxTrapEventSeverity 20 }

fgs2528kxTrapEventSeverityWarmStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { fgs2528kxTrapEventSeverity 21 }


fgs2528kxSMTP                                             OBJECT IDENTIFIER ::= { fgs2528kxConfiguration 8 }

fgs2528kxSMTPMailServer OBJECT-TYPE
   SYNTAX      DisplayString
   MAX-ACCESS  read-write
   STATUS      current
   DESCRIPTION
       " Up to 47 characters describing email server. "
   ::= { fgs2528kxSMTP 1 }

fgs2528kxSMTPUserName OBJECT-TYPE
   SYNTAX      DisplayString
   MAX-ACCESS  read-write
   STATUS      current
   DESCRIPTION
       " Up to 47 characters describing user name. "
   ::= { fgs2528kxSMTP 2 }

fgs2528kxSMTPPassword OBJECT-TYPE
   SYNTAX      DisplayString
   MAX-ACCESS  read-write
   STATUS      current
   DESCRIPTION
       " Up to 47 characters describing password. "
   ::= { fgs2528kxSMTP 3 }

fgs2528kxSMTPServeriryLevel OBJECT-TYPE
   SYNTAX      INTEGER(0..7)
   MAX-ACCESS  read-write
   STATUS      current
   DESCRIPTION
       "default: 6
       0: Emergency
       1: Alert
       2: Critical
       3: Error
       4: Warning
       5: Notice
       6: Info
       7: Debug"
   ::= { fgs2528kxSMTP 4 }

fgs2528kxSMTPSender OBJECT-TYPE
   SYNTAX      DisplayString
   MAX-ACCESS  read-write
   STATUS      current
   DESCRIPTION
       " Up to 47 characters describing sender. "
   ::= { fgs2528kxSMTP 5 }

fgs2528kxSMTPReturnPath OBJECT-TYPE
   SYNTAX      DisplayString
   MAX-ACCESS  read-write
   STATUS      current
   DESCRIPTION
       " Up to 47 characters describing return path. "
   ::= { fgs2528kxSMTP 6 }

fgs2528kxSMTPEmailAddress1 OBJECT-TYPE
   SYNTAX      DisplayString
   MAX-ACCESS  read-write
   STATUS      current
   DESCRIPTION
       " Up to 47 characters describing mail address. "
   ::= { fgs2528kxSMTP 7 }

fgs2528kxSMTPEmailAddress2 OBJECT-TYPE
   SYNTAX      DisplayString
   MAX-ACCESS  read-write
   STATUS      current
   DESCRIPTION
       " Up to 47 characters describing mail address. "
   ::= { fgs2528kxSMTP 8 }

fgs2528kxSMTPEmailAddress3 OBJECT-TYPE
   SYNTAX      DisplayString
   MAX-ACCESS  read-write
   STATUS      current
   DESCRIPTION
       " Up to 47 characters describing mail address. "
   ::= { fgs2528kxSMTP 9 }

fgs2528kxSMTPEmailAddress4 OBJECT-TYPE
   SYNTAX      DisplayString
   MAX-ACCESS  read-write
   STATUS      current
   DESCRIPTION
       " Up to 47 characters describing mail address. "
   ::= { fgs2528kxSMTP 10 }

fgs2528kxSMTPEmailAddress5 OBJECT-TYPE
   SYNTAX      DisplayString
   MAX-ACCESS  read-write
   STATUS      current
   DESCRIPTION
       " Up to 47 characters describing mail address. "
   ::= { fgs2528kxSMTP 11 }

fgs2528kxSMTPEmailAddress6 OBJECT-TYPE
   SYNTAX      DisplayString
   MAX-ACCESS  read-write
   STATUS      current
   DESCRIPTION
       " Up to 47 characters describing mail address. "
   ::= { fgs2528kxSMTP 12 }


fgs2528kxACL                                                   OBJECT IDENTIFIER ::= { fgs2528kxConfiguration 9 }

fgs2528kxACLPortsConfTable OBJECT-TYPE
   SYNTAX      SEQUENCE OF FGS2528KXACLPortsConfEntry
   MAX-ACCESS  not-accessible
   STATUS      current
   DESCRIPTION
       " "
   ::= { fgs2528kxACL 1 }

fgs2528kxACLPortsConfEntry OBJECT-TYPE
   SYNTAX      FGS2528KXACLPortsConfEntry
   MAX-ACCESS  not-accessible
   STATUS      current
   DESCRIPTION
       ""
   INDEX    { fgs2528kxACLPortsConfPort  }
   ::= { fgs2528kxACLPortsConfTable 1 }

FGS2528KXACLPortsConfEntry ::= SEQUENCE {
   fgs2528kxACLPortsConfPort               INTEGER,
   fgs2528kxACLPortsConfPolicyID           INTEGER,
   fgs2528kxACLPortsConfAction             INTEGER,
   fgs2528kxACLPortsConfRateLimiterID      INTEGER,
   fgs2528kxACLPortsConfPortRedirect       INTEGER,
   fgs2528kxACLPortsConfLogging            INTEGER,
   fgs2528kxACLPortsConfShutdown           INTEGER,
   fgs2528kxACLPortsConfState              INTEGER,
   fgs2528kxACLPortsConfCounter            Counter32
}

fgs2528kxACLPortsConfPort OBJECT-TYPE
   SYNTAX      INTEGER (1..4095)
   MAX-ACCESS  not-accessible
   STATUS      current
   DESCRIPTION
       " "
   ::= { fgs2528kxACLPortsConfEntry 1 }

fgs2528kxACLPortsConfPolicyID OBJECT-TYPE
   SYNTAX      INTEGER (0..255)
   MAX-ACCESS  read-write
   STATUS      current
   DESCRIPTION
       "default: 0, range : 0 - 255 "
   ::= { fgs2528kxACLPortsConfEntry 2 }

fgs2528kxACLPortsConfAction OBJECT-TYPE
   SYNTAX      INTEGER(0|1)
   MAX-ACCESS  read-write
   STATUS      current
   DESCRIPTION
       "default: 1,
        0: Deny
        1: Permit"
   ::= { fgs2528kxACLPortsConfEntry 3 }

fgs2528kxACLPortsConfRateLimiterID OBJECT-TYPE
   SYNTAX      INTEGER (0..16)
   MAX-ACCESS  read-write
   STATUS      current
   DESCRIPTION
       "default: 0,
        0: Disable
        range : 0 - 16 "
   ::= { fgs2528kxACLPortsConfEntry 4 }

fgs2528kxACLPortsConfPortRedirect OBJECT-TYPE
   SYNTAX      INTEGER (0..4095)
   MAX-ACCESS  read-write
   STATUS      current
   DESCRIPTION
       "default: 0
        0: Disable
        range : 0 - end port number "
   ::= { fgs2528kxACLPortsConfEntry 5 }

fgs2528kxACLPortsConfLogging OBJECT-TYPE
   SYNTAX      INTEGER(0|1)
   MAX-ACCESS  read-write
   STATUS      current
   DESCRIPTION
       "default: 0
        0: Disable
        1: Enable "
   ::= { fgs2528kxACLPortsConfEntry 7 }

fgs2528kxACLPortsConfShutdown OBJECT-TYPE
   SYNTAX      INTEGER(0|1)
   MAX-ACCESS  read-write
   STATUS      current
   DESCRIPTION
       "default: 0
        0: Disable
        1: Enable "
   ::= { fgs2528kxACLPortsConfEntry 8 }

fgs2528kxACLPortsConfState OBJECT-TYPE
   SYNTAX      INTEGER(0|1)
   MAX-ACCESS  read-write
   STATUS      current
   DESCRIPTION
       "default: 1
        0: Disable
        1: Enable "
   ::= { fgs2528kxACLPortsConfEntry 9 }

fgs2528kxACLPortsConfCounter OBJECT-TYPE
   SYNTAX      Counter32
   MAX-ACCESS  read-only
   STATUS      current
   DESCRIPTION
       "Counts the number of frames that match this ACE. "
   ::= { fgs2528kxACLPortsConfEntry 10 }


fgs2528kxACLRateLimiterTable OBJECT-TYPE
   SYNTAX      SEQUENCE OF FGS2528KXACLRateLimiterEntry
   MAX-ACCESS  not-accessible
   STATUS      current
   DESCRIPTION
       " "
   ::= { fgs2528kxACL 2 }

fgs2528kxACLRateLimiterEntry OBJECT-TYPE
   SYNTAX      FGS2528KXACLRateLimiterEntry
   MAX-ACCESS  not-accessible
   STATUS      current
   DESCRIPTION
       ""
   INDEX    { fgs2528kxACLRateLimiterID  }
   ::= { fgs2528kxACLRateLimiterTable 1 }

FGS2528KXACLRateLimiterEntry ::= SEQUENCE {
   fgs2528kxACLRateLimiterID       INTEGER,
   fgs2528kxACLRateLimiterRate     INTEGER
}

fgs2528kxACLRateLimiterID OBJECT-TYPE
   SYNTAX      INTEGER (1..16)
   MAX-ACCESS  not-accessible
   STATUS      current
   DESCRIPTION
       " Rate Limiter ID.
         range : 1-16 "
   ::= { fgs2528kxACLRateLimiterEntry 1 }

fgs2528kxACLRateLimiterRate OBJECT-TYPE
   SYNTAX      INTEGER (0..3276700)
   MAX-ACCESS  read-write
   STATUS      current
   DESCRIPTION
       "default: 1,
        range : <0-3276700> pps
       "
   ::= { fgs2528kxACLRateLimiterEntry 3 }


fgs2528kxACLACE                                          OBJECT IDENTIFIER ::= { fgs2528kxACL 3 }

fgs2528kxACLACECreate OBJECT-TYPE
   SYNTAX       INTEGER(0|1)
   MAX-ACCESS   read-write
   STATUS       current
   DESCRIPTION
       "default: 0
        0 : None  (read only)
        1 : Create an ACE entry"
   ::= { fgs2528kxACLACE 1 }

fgs2528kxACLACETable OBJECT-TYPE
   SYNTAX      SEQUENCE OF FGS2528KXACLACEEntry
   MAX-ACCESS  not-accessible
   STATUS      current
   DESCRIPTION
       " Create ACL ACE entry. "
   ::= { fgs2528kxACLACE 2 }

fgs2528kxACLACEEntry OBJECT-TYPE
   SYNTAX      FGS2528KXACLACEEntry
   MAX-ACCESS  not-accessible
   STATUS      current
   DESCRIPTION
       ""
   INDEX    { fgs2528kxACLACEIndex  }
   ::= { fgs2528kxACLACETable 1 }

FGS2528KXACLACEEntry ::= SEQUENCE {
   fgs2528kxACLACEIndex                INTEGER,
   fgs2528kxACLACEID                   INTEGER,
   fgs2528kxACLACENextID               INTEGER,
   fgs2528kxACLACEIngressPort          DisplayString,
   fgs2528kxACLACEPortPolicyNumber     INTEGER,

   fgs2528kxACLACEPortPolicyBitmask    INTEGER,
   fgs2528kxACLACEFrameType            INTEGER,
   fgs2528kxACLACEAction               INTEGER,
   fgs2528kxACLACEDenyPortRedirect     DisplayString,
   fgs2528kxACLACELogging              INTEGER,

   fgs2528kxACLACERateLimiter          INTEGER,
   fgs2528kxACLACEShutdown             INTEGER,
   fgs2528kxACLACEVLANTagPriority      INTEGER,

   fgs2528kxACLACEVLANVID              INTEGER,
   fgs2528kxACLACEEtherType            INTEGER,
   fgs2528kxACLACESMAC                 DisplayString,
   fgs2528kxACLACEDMACType             INTEGER,
   fgs2528kxACLACEDMAC                 DisplayString,

   fgs2528kxACLACEArpOpcode            INTEGER,
   fgs2528kxACLACEArpFlagsRequestReply INTEGER,
   fgs2528kxACLACEArpFlagsArpSmac      INTEGER,
   fgs2528kxACLACEArpFlagsRarpDmac     INTEGER,
   fgs2528kxACLACEArpFlagsLength       INTEGER,

   fgs2528kxACLACEArpFlagsIp           INTEGER,
   fgs2528kxACLACEArpFlagsEthernet     INTEGER,
   fgs2528kxACLACESIPType              INTEGER,
   fgs2528kxACLACESIPIPAddress         IpAddress,
   fgs2528kxACLACESIPNetworkPrefix     INTEGER,

   fgs2528kxACLACEDIPType              INTEGER,
   fgs2528kxACLACEDIPIPAddress         IpAddress,
   fgs2528kxACLACEDIPNetworkPrefix     INTEGER,

   fgs2528kxACLACEIPProtocol           INTEGER,
   fgs2528kxACLACEIPFlagsTTL           INTEGER,
   fgs2528kxACLACEIPFlagsOptions       INTEGER,
   fgs2528kxACLACEIPFlagsFragment      INTEGER,
   fgs2528kxACLACEICMPType             INTEGER,

   fgs2528kxACLACEICMPCode             INTEGER,
   fgs2528kxACLACESourcePortMin        INTEGER,
   fgs2528kxACLACESourcePortMax        INTEGER,
   fgs2528kxACLACEDestPortMin          INTEGER,
   fgs2528kxACLACEDestPortMax          INTEGER,

   fgs2528kxACLACETCPFlagsFin          INTEGER,
   fgs2528kxACLACETCPFlagsSyn          INTEGER,
   fgs2528kxACLACETCPFlagsRst          INTEGER,
   fgs2528kxACLACETCPFlagsPsh          INTEGER,
   fgs2528kxACLACETCPFlagsAck          INTEGER,

   fgs2528kxACLACETCPFlagsUrg          INTEGER,

   fgs2528kxACLACERowStatus            INTEGER
}

fgs2528kxACLACEIndex OBJECT-TYPE
   SYNTAX      INTEGER (1..256)
   MAX-ACCESS  not-accessible
   STATUS      current
   DESCRIPTION
       " "
   ::= { fgs2528kxACLACEEntry 1 }

fgs2528kxACLACEID OBJECT-TYPE
   SYNTAX      INTEGER (1..256)
   MAX-ACCESS  read-write
   STATUS      current
   DESCRIPTION
       " If the ACE ID is specified and an entry with this ACE ID
         already exists, the ACE will be modified. Otherwise, a
         new ACE will be added.
         range : 1 - 256. "
   ::= { fgs2528kxACLACEEntry 2 }

fgs2528kxACLACENextID OBJECT-TYPE
   SYNTAX      INTEGER (0..256)
   MAX-ACCESS  read-write
   STATUS      current
   DESCRIPTION
       " If the next ACE ID is non zero, the ACE will be placed
         before this ACE in the list. If the next ACE ID is zero,
         the ACE will be placed last in the list.
         range : 0 - 256. "
   ::= { fgs2528kxACLACEEntry 3 }

fgs2528kxACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { fgs2528kxACLACEEntry 4 }

fgs2528kxACLACEPortPolicyNumber OBJECT-TYPE
   SYNTAX      INTEGER (0..255)
   MAX-ACCESS  read-write
   STATUS      current
   DESCRIPTION
       " policy value.
         range : 0 - 255. "
   ::= { fgs2528kxACLACEEntry 5 }

fgs2528kxACLACEPortPolicyBitmask OBJECT-TYPE
   SYNTAX      INTEGER (0..255)
   MAX-ACCESS  read-write
   STATUS      current
   DESCRIPTION
       " policy bitmask.
         range : 0 - 255(0xff). "
   ::= { fgs2528kxACLACEEntry 6 }

fgs2528kxACLACEFrameType OBJECT-TYPE
   SYNTAX      INTEGER (0..6)
   MAX-ACCESS  read-write
   STATUS      current
   DESCRIPTION
       " 0: any,
         1: arp,
         2: etype,
         3: icmp,
         4: ipv4,
         5: tcp,
         6: udp."
   ::= { fgs2528kxACLACEEntry 7 }

fgs2528kxACLACEAction OBJECT-TYPE
   SYNTAX      INTEGER(0|1)
   MAX-ACCESS  read-write
   STATUS      current
   DESCRIPTION
       "default: 1,
        0: Deny
        1: Permit"
   ::= { fgs2528kxACLACEEntry 8 }

fgs2528kxACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { fgs2528kxACLACEEntry 9 }

fgs2528kxACLACELogging OBJECT-TYPE
   SYNTAX      INTEGER(0|1)
   MAX-ACCESS  read-write
   STATUS      current
   DESCRIPTION
       "default: 0,
        0: disable - Frames matching the ACE are not logged.
        1: enable - Frames matching the ACE are stored in the system log."
   ::= { fgs2528kxACLACEEntry 10 }

fgs2528kxACLACERateLimiter OBJECT-TYPE
   SYNTAX      INTEGER (0..16)
   MAX-ACCESS  read-write
   STATUS      current
   DESCRIPTION
       "default: 0,
        0: Disable
        range : 0 - 16 "
   ::= { fgs2528kxACLACEEntry 12 }

fgs2528kxACLACEShutdown OBJECT-TYPE
   SYNTAX      INTEGER(0|1)
   MAX-ACCESS  read-write
   STATUS      current
   DESCRIPTION
       "default: 0,
        0: disable - Port shut down is disabled for the AC.
        1: enable - If a frame matches the ACE, the ingress port will be disabled."
   ::= { fgs2528kxACLACEEntry 13 }

fgs2528kxACLACEVLANTagPriority OBJECT-TYPE
   SYNTAX      INTEGER (0..8)
   MAX-ACCESS  read-write
   STATUS      current
   DESCRIPTION
       "Specify the tag priority for this ACE.
        The tag priority can't be set when 802.1Q Tagged is disabled
        default: 8,
        8: Any,
        range : 0 - 8 "
   ::= { fgs2528kxACLACEEntry 15 }

fgs2528kxACLACEVLANVID OBJECT-TYPE
   SYNTAX      INTEGER (0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { fgs2528kxACLACEEntry 16 }

fgs2528kxACLACEEtherType OBJECT-TYPE
   SYNTAX      INTEGER (0..65535)
   MAX-ACCESS  read-write
   STATUS      current
   DESCRIPTION
       " 0: Any - Any but excluding 0x0800(IPv4) 0x0806(ARP) and 0x86DD(IPv6).
         range : 0 or 1536(0x0600)- 65535(0xffff). "
   ::= { fgs2528kxACLACEEntry 17 }

fgs2528kxACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { fgs2528kxACLACEEntry 18 }

fgs2528kxACLACEDMACType OBJECT-TYPE
   SYNTAX      INTEGER (0..4)
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address
        range : 0 - 4 "
   ::= { fgs2528kxACLACEEntry 19 }

fgs2528kxACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { fgs2528kxACLACEEntry 20 }

fgs2528kxACLACEArpOpcode OBJECT-TYPE
   SYNTAX      INTEGER (0..3)
   MAX-ACCESS  read-write
   STATUS      current
   DESCRIPTION
       "Configure ARP opcode for this ACE.
        default: 0,
        0: Any - Don't care.
        1: arp.
        2: rarp.
        3: other.
        4: No data.
        range : 0 - 3 "
   ::= { fgs2528kxACLACEEntry 21 }

fgs2528kxACLACEArpFlagsRequestReply OBJECT-TYPE
   SYNTAX      INTEGER (0..2)
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 2 "
   ::= { fgs2528kxACLACEEntry 22 }

fgs2528kxACLACEArpFlagsArpSmac OBJECT-TYPE
   SYNTAX      INTEGER (0..2)
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 2 "
   ::= { fgs2528kxACLACEEntry 23 }

fgs2528kxACLACEArpFlagsRarpDmac OBJECT-TYPE
   SYNTAX      INTEGER (0..2)
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 2 "
   ::= { fgs2528kxACLACEEntry 24 }

fgs2528kxACLACEArpFlagsLength OBJECT-TYPE
   SYNTAX      INTEGER (0..2)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 2 "
   ::= { fgs2528kxACLACEEntry 25 }

fgs2528kxACLACEArpFlagsIp OBJECT-TYPE
   SYNTAX      INTEGER (0..2)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 2 "
   ::= { fgs2528kxACLACEEntry 26 }

fgs2528kxACLACEArpFlagsEthernet OBJECT-TYPE
   SYNTAX      INTEGER (0..2)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 2 "
   ::= { fgs2528kxACLACEEntry 27 }

fgs2528kxACLACESIPType OBJECT-TYPE
   SYNTAX      INTEGER(0|1)
   MAX-ACCESS  read-write
   STATUS      current
   DESCRIPTION
       "Configure source IP address for this ACE.
        default: 0,
        0: Any - Don't care.
        1: IP Address.
        2: No data.
        range : 0 - 1"
   ::= { fgs2528kxACLACEEntry 28 }

fgs2528kxACLACESIPIPAddress OBJECT-TYPE
   SYNTAX      IpAddress
   MAX-ACCESS  read-write
   STATUS      current
   DESCRIPTION
       "A frame that hits this ACE matches this source IP address value."
   ::= { fgs2528kxACLACEEntry 29 }

fgs2528kxACLACESIPNetworkPrefix OBJECT-TYPE
   SYNTAX      INTEGER (1..32)
   MAX-ACCESS  read-write
   STATUS      current
   DESCRIPTION
       "Network prefix.
        default: 32,
        0: No data.
        range : 1 - 32"
   ::= { fgs2528kxACLACEEntry 30 }


fgs2528kxACLACEDIPType OBJECT-TYPE
   SYNTAX      INTEGER(0|1)
   MAX-ACCESS  read-write
   STATUS      current
   DESCRIPTION
       "Configure destination IP address for this ACE.
        default: 0,
        0: Any - Don't care.
        1: IP Address.
        2: No data.
        range : 0 - 1"
   ::= { fgs2528kxACLACEEntry 32 }

fgs2528kxACLACEDIPIPAddress OBJECT-TYPE
   SYNTAX      IpAddress
   MAX-ACCESS  read-write
   STATUS      current
   DESCRIPTION
       "A frame that hits this ACE matches this destination IP address value."
   ::= { fgs2528kxACLACEEntry 33 }

fgs2528kxACLACEDIPNetworkPrefix OBJECT-TYPE
   SYNTAX      INTEGER (1..32)
   MAX-ACCESS  read-write
   STATUS      current
   DESCRIPTION
       "Network prefix.
        default: 32,
        0: No data.
        range : 1 - 32"
   ::= { fgs2528kxACLACEEntry 34 }


fgs2528kxACLACEIPProtocol OBJECT-TYPE
   SYNTAX      INTEGER (0..256)
   MAX-ACCESS  read-write
   STATUS      current
   DESCRIPTION
       "Configure IP protocol for this ACE.
        default: 256,
        256: Any - Don't care.
        257: No data.
        range : 0 - 256"
   ::= { fgs2528kxACLACEEntry 36 }

fgs2528kxACLACEIPFlagsTTL OBJECT-TYPE
   SYNTAX      INTEGER (0..2)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 2 "
   ::= { fgs2528kxACLACEEntry 37 }

fgs2528kxACLACEIPFlagsOptions OBJECT-TYPE
   SYNTAX      INTEGER (0..2)
   MAX-ACCESS  read-write
   STATUS      current
   DESCRIPTION
       "Configure IP options flag for this ACE.
        default: 2,
        0: IPv4 frames where the options flag is unset.
        1: IPv4 frames where the options flag is set.
        2: Any - Don't care.
        3: No data.
        range : 0 - 2 "
   ::= { fgs2528kxACLACEEntry 38 }

fgs2528kxACLACEIPFlagsFragment OBJECT-TYPE
   SYNTAX      INTEGER (0..2)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 2 "
   ::= { fgs2528kxACLACEEntry 39 }

fgs2528kxACLACEICMPType OBJECT-TYPE
   SYNTAX      INTEGER (0..256)
   MAX-ACCESS  read-write
   STATUS      current
   DESCRIPTION
       "Configure ICMP type for this ACE.
        default: 256,
        256: Any - Don't care.
        257: No data.
        range : 0 - 256"
   ::= { fgs2528kxACLACEEntry 40 }

fgs2528kxACLACEICMPCode OBJECT-TYPE
   SYNTAX      INTEGER (0..256)
   MAX-ACCESS  read-write
   STATUS      current
   DESCRIPTION
       "Configure ICMP code for this ACE.
        default: 256,
        256: Any - Don't care.
        257: No data.
        range : 0 - 256"
   ::= { fgs2528kxACLACEEntry 41 }

fgs2528kxACLACESourcePortMin OBJECT-TYPE
   SYNTAX      INTEGER (0..65535)
   MAX-ACCESS  read-write
   STATUS      current
   DESCRIPTION
       "Configure Source UDP/TCP port range for this ACE.
        default: 0,
        65536: No data.
        range : 0 - 65535"
   ::= { fgs2528kxACLACEEntry 42 }

fgs2528kxACLACESourcePortMax OBJECT-TYPE
   SYNTAX      INTEGER (0..65535)
   MAX-ACCESS  read-write
   STATUS      current
   DESCRIPTION
       "Configure Source UDP/TCP port range for this ACE.
        default: 0,
        65536: No data.
        range : 0 - 65535"
   ::= { fgs2528kxACLACEEntry 43 }

fgs2528kxACLACEDestPortMin OBJECT-TYPE
   SYNTAX      INTEGER (0..65535)
   MAX-ACCESS  read-write
   STATUS      current
   DESCRIPTION
       "Configure Destination UDP/TCP port range for this ACE.
        default: 0,
        65536: No data.
        range : 0 - 65535"
   ::= { fgs2528kxACLACEEntry 44 }

fgs2528kxACLACEDestPortMax OBJECT-TYPE
   SYNTAX      INTEGER (0..65535)
   MAX-ACCESS  read-write
   STATUS      current
   DESCRIPTION
       "Configure Destination UDP/TCP port range for this ACE.
        default: 0,
        65536: No data.
        range : 0 - 65535"
   ::= { fgs2528kxACLACEEntry 45 }

fgs2528kxACLACETCPFlagsFin OBJECT-TYPE
   SYNTAX      INTEGER (0..2)
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 2 "
   ::= { fgs2528kxACLACEEntry 46 }

fgs2528kxACLACETCPFlagsSyn OBJECT-TYPE
   SYNTAX      INTEGER (0..2)
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 2 "
   ::= { fgs2528kxACLACEEntry 47 }

fgs2528kxACLACETCPFlagsRst OBJECT-TYPE
   SYNTAX      INTEGER (0..2)
   MAX-ACCESS  read-write
   STATUS      current
   DESCRIPTION
       "Configure TCP (RST) flags for this ACE.
        default: 2,
        0: TCP frames where the RST field is unset.
        1: TCP frames where the RST field is set.
        2: Any - Don't care.
        3: No data.
        range : 0 - 2 "
   ::= { fgs2528kxACLACEEntry 48 }

fgs2528kxACLACETCPFlagsPsh OBJECT-TYPE
   SYNTAX      INTEGER (0..2)
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 2 "
   ::= { fgs2528kxACLACEEntry 49 }

fgs2528kxACLACETCPFlagsAck OBJECT-TYPE
   SYNTAX      INTEGER (0..2)
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 2 "
   ::= { fgs2528kxACLACEEntry 50 }

fgs2528kxACLACETCPFlagsUrg OBJECT-TYPE
   SYNTAX      INTEGER (0..2)
   MAX-ACCESS  read-write
   STATUS      current
   DESCRIPTION
       "Configure TCP (URG) flags for this ACE.
        default: 2,
        0: TCP frames where the URG field is unset.
        1: TCP frames where the URG field is set.
        2: Any - Don't care.
        3: No data.
        range : 0 - 2 "
   ::= { fgs2528kxACLACEEntry 51 }

fgs2528kxACLACERowStatus OBJECT-TYPE
   SYNTAX      INTEGER (1..5)
   MAX-ACCESS  read-write
   STATUS      current
   DESCRIPTION
       " 1: active
         2: notInservice
         4: destroy
         5: undo"
   ::= { fgs2528kxACLACEEntry 66 }


fgs2528kxACLACEClear OBJECT-TYPE
   SYNTAX       INTEGER(0|1)
   MAX-ACCESS   read-write
   STATUS       current
   DESCRIPTION
       "default: 0
        0 : No action
        1 : Clear all ACL counters."
   ::= { fgs2528kxACLACE 3 }

fgs2528kxACLACEMoveACEID OBJECT-TYPE
   SYNTAX       INTEGER (1..256)
   MAX-ACCESS   read-write
   STATUS       current
   DESCRIPTION
       "Move ACE,
        default: 0
        ACE ID must be exist.
        range : 1 - 256."
   ::= { fgs2528kxACLACE 4 }

fgs2528kxACLACEMoveNextACEID OBJECT-TYPE
   SYNTAX       INTEGER (0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { fgs2528kxACLACE 5 }

fgs2528kxACLACEStatusTable OBJECT-TYPE
   SYNTAX      SEQUENCE OF FGS2528KXACLACEStatusEntry
   MAX-ACCESS  not-accessible
   STATUS      current
   DESCRIPTION
       " ACL ACE Status entry. "
   ::= { fgs2528kxACLACE 6 }

fgs2528kxACLACEStatusEntry OBJECT-TYPE
   SYNTAX      FGS2528KXACLACEStatusEntry
   MAX-ACCESS  not-accessible
   STATUS      current
   DESCRIPTION
       ""
   INDEX    { fgs2528kxACLACEStatusIndex  }
   ::= { fgs2528kxACLACEStatusTable 1 }

FGS2528KXACLACEStatusEntry ::= SEQUENCE {
   fgs2528kxACLACEStatusIndex          INTEGER,
   fgs2528kxACLACEStatusUser           DisplayString,
   fgs2528kxACLACEStatusID             INTEGER,
   fgs2528kxACLACEStatusIngressPort    DisplayString,
   fgs2528kxACLACEStatusFrameType      DisplayString,
   fgs2528kxACLACEStatusAction         DisplayString,
   fgs2528kxACLACEStatusRateLimiter    DisplayString,
   fgs2528kxACLACEStatusPortCopy       DisplayString,
   fgs2528kxACLACEStatusMirror         DisplayString,
   fgs2528kxACLACEStatusCPU            DisplayString,
   fgs2528kxACLACEStatusCounter        Counter32,
   fgs2528kxACLACEStatusConflict       DisplayString
}

fgs2528kxACLACEStatusIndex OBJECT-TYPE
   SYNTAX      INTEGER (1..256)
   MAX-ACCESS  not-accessible
   STATUS      current
   DESCRIPTION
       " "
   ::= { fgs2528kxACLACEStatusEntry 1 }

fgs2528kxACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { fgs2528kxACLACEStatusEntry 2 }

fgs2528kxACLACEStatusID OBJECT-TYPE
   SYNTAX      INTEGER (1..256)
   MAX-ACCESS  read-only
   STATUS      current
   DESCRIPTION
       " ACE ID.
         range : 1 - 256. "
   ::= { fgs2528kxACLACEStatusEntry 3 }

fgs2528kxACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { fgs2528kxACLACEStatusEntry 4 }

fgs2528kxACLACEStatusFrameType OBJECT-TYPE
   SYNTAX      DisplayString
   MAX-ACCESS  read-only
   STATUS      current
   DESCRIPTION
       " Indicates the frame type of the ACE. "
   ::= { fgs2528kxACLACEStatusEntry 5 }

fgs2528kxACLACEStatusAction OBJECT-TYPE
   SYNTAX      DisplayString
   MAX-ACCESS  read-only
   STATUS      current
   DESCRIPTION
       " Indicates the forwarding action of the ACE. "
   ::= { fgs2528kxACLACEStatusEntry 6 }

fgs2528kxACLACEStatusRateLimiter OBJECT-TYPE
   SYNTAX      DisplayString
   MAX-ACCESS  read-only
   STATUS      current
   DESCRIPTION
       " Indicates the rate limiter number of the ACE. "
   ::= { fgs2528kxACLACEStatusEntry 7 }

fgs2528kxACLACEStatusPortCopy OBJECT-TYPE
   SYNTAX      DisplayString
   MAX-ACCESS  read-only
   STATUS      current
   DESCRIPTION
       " Indicates the port redirect operation of the ACE. Frames matching the ACE are redirected to the port number. "
   ::= { fgs2528kxACLACEStatusEntry 8 }

fgs2528kxACLACEStatusMirror OBJECT-TYPE
   SYNTAX      DisplayString
   MAX-ACCESS  read-only
   STATUS      current
   DESCRIPTION
       " Specify the mirror operation of this port. "
   ::= { fgs2528kxACLACEStatusEntry 9 }

fgs2528kxACLACEStatusCPU OBJECT-TYPE
   SYNTAX      DisplayString
   MAX-ACCESS  read-only
   STATUS      current
   DESCRIPTION
       " Forward packet that matched the specific ACE to CPU. "
   ::= { fgs2528kxACLACEStatusEntry 10 }

fgs2528kxACLACEStatusCounter OBJECT-TYPE
   SYNTAX      Counter32
   MAX-ACCESS  read-only
   STATUS      current
   DESCRIPTION
       " The counter indicates the number of times the ACE was hit by a frame. "
   ::= { fgs2528kxACLACEStatusEntry 11 }

fgs2528kxACLACEStatusConflict OBJECT-TYPE
   SYNTAX      DisplayString
   MAX-ACCESS  read-only
   STATUS      current
   DESCRIPTION
       " Indicates the hardware status of the specific ACE. The specific ACE is not applied to the hardware due to hardware limitations. "
   ::= { fgs2528kxACLACEStatusEntry 12 }


fgs2528kxERPS                                             OBJECT IDENTIFIER ::= { fgs2528kxConfiguration 10 }

fgs2528kxERPSConf                                          OBJECT IDENTIFIER ::= { fgs2528kxERPS 1 }

fgs2528kxERPSConfCreate OBJECT-TYPE
   SYNTAX       INTEGER(0|1)
   MAX-ACCESS   read-write
   STATUS       current
   DESCRIPTION
       "default: 0
        0 : None  (read only)
        1 : Create an ERPS entry"
   ::= { fgs2528kxERPSConf 1 }

fgs2528kxERPSConfTable OBJECT-TYPE
   SYNTAX      SEQUENCE OF FGS2528KXERPSConfEntry
   MAX-ACCESS  not-accessible
   STATUS      current
   DESCRIPTION
       " Create one ERPS group. "
   ::= { fgs2528kxERPSConf 2 }

fgs2528kxERPSConfEntry OBJECT-TYPE
   SYNTAX      FGS2528KXERPSConfEntry
   MAX-ACCESS  not-accessible
   STATUS      current
   DESCRIPTION
       ""
   INDEX    { fgs2528kxERPSConfIndex  }
   ::= { fgs2528kxERPSConfTable 1 }

FGS2528KXERPSConfEntry ::= SEQUENCE {
   fgs2528kxERPSConfIndex                  INTEGER,
   fgs2528kxERPSConfERPSID                 INTEGER,
   fgs2528kxERPSConfPort0                  INTEGER,
   fgs2528kxERPSConfPort1                  INTEGER,
   fgs2528kxERPSConfPort0SFMEP             INTEGER,
   fgs2528kxERPSConfPort1SFMEP             INTEGER,
   fgs2528kxERPSConfPort0APSMEP            INTEGER,
   fgs2528kxERPSConfPort1APSMEP            INTEGER,
   fgs2528kxERPSConfRingType               INTEGER,
   fgs2528kxERPSConfInterconnectedNode     INTEGER,
   fgs2528kxERPSConfVirtualChannel         INTEGER,
   fgs2528kxERPSConfMajorRingID            INTEGER,
   fgs2528kxERPSConfAlarm                  DisplayString,

   fgs2528kxERPSInstanceConfConfigured     DisplayString,
   fgs2528kxERPSInstanceConfGuardTime      INTEGER,
   fgs2528kxERPSInstanceConfWTRTime        INTEGER,
   fgs2528kxERPSInstanceConfHoldOffTime    INTEGER,
   fgs2528kxERPSInstanceConfVersion        INTEGER,
   fgs2528kxERPSInstanceConfRevertive      INTEGER,
   fgs2528kxERPSInstanceConfVLANconfig     DisplayString,

   fgs2528kxERPSConfRowStatus              INTEGER
}

fgs2528kxERPSConfIndex OBJECT-TYPE
   SYNTAX      INTEGER (1..64)
   MAX-ACCESS  not-accessible
   STATUS      current
   DESCRIPTION
       " "
   ::= { fgs2528kxERPSConfEntry 1 }

fgs2528kxERPSConfERPSID OBJECT-TYPE
   SYNTAX      INTEGER (1..64)
   MAX-ACCESS  read-write
   STATUS      current
   DESCRIPTION
       " Protection group ID.
         range : 1 - 64. "
   ::= { fgs2528kxERPSConfEntry 2 }

fgs2528kxERPSConfPort0 OBJECT-TYPE
   SYNTAX      INTEGER (1..26)
   MAX-ACCESS  read-write
   STATUS      current
   DESCRIPTION
       " East port of the switch in the ring.
         range : 1 - 26. "
   ::= { fgs2528kxERPSConfEntry 3 }

fgs2528kxERPSConfPort1 OBJECT-TYPE
   SYNTAX      INTEGER (0..26)
   MAX-ACCESS  read-write
   STATUS      current
   DESCRIPTION
       " West port of the switch in the Ring.
         As interconnected sub-ring will have only one ring port, W port is configured as 0 for interconnected sub-ring.
         0: in this field indicates that no west port is associated with this instance.
         range : 0 - 26. "
   ::= { fgs2528kxERPSConfEntry 4 }

fgs2528kxERPSConfPort0SFMEP OBJECT-TYPE
   SYNTAX      INTEGER (1..32)
   MAX-ACCESS  read-write
   STATUS      current
   DESCRIPTION
       " The East Signal Fail reporting MEP.
         range : 1 - 32. "
   ::= { fgs2528kxERPSConfEntry 5 }

fgs2528kxERPSConfPort1SFMEP OBJECT-TYPE
   SYNTAX      INTEGER (0..32)
   MAX-ACCESS  read-write
   STATUS      current
   DESCRIPTION
       " The West Signal Fail reporting MEP. As only one SF MEP is associated with interconnected sub-ring without virtual channel,
         it is configured as 0 for such ring instances. 0: in this field indicates that no west SF MEP is associated with this instance.
         range : 0 - 32. "
   ::= { fgs2528kxERPSConfEntry 6 }

fgs2528kxERPSConfPort0APSMEP OBJECT-TYPE
   SYNTAX      INTEGER (1..32)
   MAX-ACCESS  read-write
   STATUS      current
   DESCRIPTION
       " The East APS PDU handling MEP.
         range : 1 - 32. "
   ::= { fgs2528kxERPSConfEntry 7 }

fgs2528kxERPSConfPort1APSMEP OBJECT-TYPE
   SYNTAX      INTEGER (0..32)
   MAX-ACCESS  read-write
   STATUS      current
   DESCRIPTION
       " The West APS PDU handling MEP. As only one APS MEP is associated with interconnected sub-ring without virtual channel,
         it is configured as 0 for such ring instances. 0: in this field indicates that no west APS MEP is associated with this instance.
         range : 0 - 32. "
   ::= { fgs2528kxERPSConfEntry 8 }

fgs2528kxERPSConfRingType OBJECT-TYPE
   SYNTAX      INTEGER (0|1)
   MAX-ACCESS  read-write
   STATUS      current
   DESCRIPTION
       " Type of Protectiong ring. It can be either major ring or sub-ring.
         default: 0,
         0: Major
         1: Sub"
   ::= { fgs2528kxERPSConfEntry 9 }

fgs2528kxERPSConfInterconnectedNode OBJECT-TYPE
   SYNTAX      INTEGER (0|1)
   MAX-ACCESS  read-write
   STATUS      current
   DESCRIPTION
       " Interconnected Node indicates that the ring instance is interconnected.
         default: 0,
         0: No - indicates that the configured instance is not interconnected.
         1: Yes - indicates it is an interconnected node for this instance. "
   ::= { fgs2528kxERPSConfEntry 10 }

fgs2528kxERPSConfVirtualChannel OBJECT-TYPE
   SYNTAX      INTEGER (0|1)
   MAX-ACCESS  read-write
   STATUS      current
   DESCRIPTION
       " Sub-rings can either have virtual channel or not on the interconnected node.
         default: 0,
         0: No - indicates, sub-ring doesn't have virtual channel.
         1: Yes - indicates it is a sub-ring with virtual channel. "
   ::= { fgs2528kxERPSConfEntry 11 }

fgs2528kxERPSConfMajorRingID OBJECT-TYPE
   SYNTAX      INTEGER (1..64)
   MAX-ACCESS  read-only
   STATUS      current
   DESCRIPTION
       " Major ring group ID for the interconnected sub-ring.
         It is used to send topology change updates on major ring.
         If ring is major, this value is same as the protection group ID of this ring. "
   ::= { fgs2528kxERPSConfEntry 12 }

fgs2528kxERPSConfAlarm OBJECT-TYPE
   SYNTAX      DisplayString (SIZE (1..32))
   MAX-ACCESS  read-only
   STATUS      current
   DESCRIPTION
       " There is an active alarm on the ERPS. "
   ::= { fgs2528kxERPSConfEntry 13 }

fgs2528kxERPSInstanceConfConfigured OBJECT-TYPE
   SYNTAX      DisplayString (SIZE (1..32))
   MAX-ACCESS  read-only
   STATUS      current
   DESCRIPTION
       " Down: This ERPS is only created and has not yet been configured - is not active.
         Up: This ERPS is configured - is active. "
   ::= { fgs2528kxERPSConfEntry 14 }

fgs2528kxERPSInstanceConfGuardTime OBJECT-TYPE
   SYNTAX      INTEGER (10..2000)
   MAX-ACCESS  read-write
   STATUS      current
   DESCRIPTION
       " Guard timeout value to be used to prevent ring nodes from receiving outdated R-APS messages.
         default : 500(ms).
         range : 10 - 2000(ms). "
   ::= { fgs2528kxERPSConfEntry 15 }

fgs2528kxERPSInstanceConfWTRTime OBJECT-TYPE
   SYNTAX      INTEGER (1..12)
   MAX-ACCESS  read-write
   STATUS      current
   DESCRIPTION
       " The Wait To Restore timing value to be used in revertive switching.
         default : 5(minutes).
         range : 1 - 12(minutes). "
   ::= { fgs2528kxERPSConfEntry 16 }

fgs2528kxERPSInstanceConfHoldOffTime OBJECT-TYPE
   SYNTAX      INTEGER (0..10000)
   MAX-ACCESS  read-write
   STATUS      current
   DESCRIPTION
       " The timing value to be used to make persistent check on Signal Fail before switching.
         default : 0(seconds).
         range : 0 - 10000(ms). "
   ::= { fgs2528kxERPSConfEntry 17 }

fgs2528kxERPSInstanceConfVersion OBJECT-TYPE
   SYNTAX      INTEGER (0|1)
   MAX-ACCESS  read-write
   STATUS      current
   DESCRIPTION
       " ERPS version of a group.
         default : 1.
         0: v1
         1: v2 "
   ::= { fgs2528kxERPSConfEntry 18 }

fgs2528kxERPSInstanceConfRevertive OBJECT-TYPE
   SYNTAX      INTEGER (0|1)
   MAX-ACCESS  read-write
   STATUS      current
   DESCRIPTION
       " ERPS revertibility of a group.
         default : 1.
         0: non-revertible
         1: revertible "
   ::= { fgs2528kxERPSConfEntry 19 }

fgs2528kxERPSInstanceConfVLANconfig OBJECT-TYPE
   SYNTAX      DisplayString (SIZE (1..255))
   MAX-ACCESS  read-write
   STATUS      current
   DESCRIPTION
       " VID of the protected vlan. "
   ::= { fgs2528kxERPSConfEntry 20 }

fgs2528kxERPSConfRowStatus OBJECT-TYPE
   SYNTAX      INTEGER (1..5)
   MAX-ACCESS  read-write
   STATUS      current
   DESCRIPTION
       " 1: active
        2: notInservice
        3: edit
        4: destroy
        5: undo"
   ::= { fgs2528kxERPSConfEntry 21 }

----------------------------------------------------------------------------------------------------------------------------
fgs2528kxSecurity                                              OBJECT IDENTIFIER ::= { fgs2528kxProductId 3 }

fgs2528kxIPSourceGuard                                         OBJECT IDENTIFIER ::= { fgs2528kxSecurity 1 }

fgs2528kxIPSourceGuardConf                                     OBJECT IDENTIFIER ::= { fgs2528kxIPSourceGuard 1 }

fgs2528kxIPSourceGuardMode OBJECT-TYPE
   SYNTAX      INTEGER (0|1)
   MAX-ACCESS  read-write
   STATUS      current
   DESCRIPTION
       " default:  0
        0: disable
        1: enable"
   ::= { fgs2528kxIPSourceGuardConf 1 }

fgs2528kxIPSourceGuardPortConfigTable OBJECT-TYPE
   SYNTAX      SEQUENCE OF FGS2528KXIPSourceGuardPortConfigEntry
   MAX-ACCESS  not-accessible
   STATUS      current
   DESCRIPTION
       " "
   ::= { fgs2528kxIPSourceGuardConf 2 }

fgs2528kxIPSourceGuardPortConfigEntry OBJECT-TYPE
   SYNTAX      FGS2528KXIPSourceGuardPortConfigEntry
   MAX-ACCESS  not-accessible
   STATUS      current
   DESCRIPTION
       ""
   INDEX    { fgs2528kxIPSourceGuardPortConfigPort  }
   ::= { fgs2528kxIPSourceGuardPortConfigTable 1 }

FGS2528KXIPSourceGuardPortConfigEntry ::= SEQUENCE {
   fgs2528kxIPSourceGuardPortConfigPort               INTEGER,
   fgs2528kxIPSourceGuardPortConfigMode               INTEGER,
   fgs2528kxIPSourceGuardPortMaxDynamicClients        INTEGER
}

fgs2528kxIPSourceGuardPortConfigPort OBJECT-TYPE
   SYNTAX      INTEGER (1..4095)
   MAX-ACCESS  not-accessible
   STATUS      current
   DESCRIPTION
       " "
   ::= { fgs2528kxIPSourceGuardPortConfigEntry 1 }

fgs2528kxIPSourceGuardPortConfigMode OBJECT-TYPE
   SYNTAX      INTEGER (0|1)
   MAX-ACCESS  read-write
   STATUS      current
   DESCRIPTION
       "default: 0
       0:disable
       1:enable "
   ::= { fgs2528kxIPSourceGuardPortConfigEntry 2 }

fgs2528kxIPSourceGuardPortMaxDynamicClients OBJECT-TYPE
   SYNTAX      INTEGER (0..2|99)
   MAX-ACCESS  read-write
   STATUS      current
   DESCRIPTION
       "default: 99
       0~2: Max Dynamic clients
       99:Unlimited "
   ::= { fgs2528kxIPSourceGuardPortConfigEntry 3 }


fgs2528kxIPSourceGuardStatic                                OBJECT IDENTIFIER ::= { fgs2528kxIPSourceGuard 2 }

fgs2528kxIPSourceGuardStaticCreate OBJECT-TYPE
   SYNTAX       INTEGER(0|1)
   MAX-ACCESS   read-write
   STATUS       current
   DESCRIPTION
       "default: 0
        0 : None  (read only)
        1 : Create a IP Source Guard"
   ::= { fgs2528kxIPSourceGuardStatic 1 }

fgs2528kxIPSourceGuardStaticTable OBJECT-TYPE
   SYNTAX      SEQUENCE OF FGS2528KXIPSourceGuardStaticEntry
   MAX-ACCESS  not-accessible
   STATUS      current
   DESCRIPTION
       " "
   ::= { fgs2528kxIPSourceGuardStatic 2 }

fgs2528kxIPSourceGuardStaticEntry OBJECT-TYPE
   SYNTAX      FGS2528KXIPSourceGuardStaticEntry
   MAX-ACCESS  not-accessible
   STATUS      current
   DESCRIPTION
       ""
   INDEX    { fgs2528kxIPSourceGuardStaticIndex  }
   ::= { fgs2528kxIPSourceGuardStaticTable 1 }

FGS2528KXIPSourceGuardStaticEntry ::= SEQUENCE {
   fgs2528kxIPSourceGuardStaticIndex         INTEGER,
   fgs2528kxIPSourceGuardStaticPort          INTEGER,
   fgs2528kxIPSourceGuardStaticVLANId        INTEGER,
   fgs2528kxIPSourceGuardStaticIPAddress     IpAddress,
   fgs2528kxIPSourceGuardStaticMACAddress    MacAddress,
   fgs2528kxIPSourceGuardStaticRowStatus     INTEGER
}

fgs2528kxIPSourceGuardStaticIndex OBJECT-TYPE
   SYNTAX      INTEGER (1..28)
   MAX-ACCESS  not-accessible
   STATUS      current
   DESCRIPTION
       " "
   ::= { fgs2528kxIPSourceGuardStaticEntry 1 }

fgs2528kxIPSourceGuardStaticPort OBJECT-TYPE
   SYNTAX      INTEGER (1..4095)
   MAX-ACCESS  read-write
   STATUS      current
   DESCRIPTION
       " Port, range: 1 - port number. "
   ::= { fgs2528kxIPSourceGuardStaticEntry 2 }

fgs2528kxIPSourceGuardStaticVLANId OBJECT-TYPE
   SYNTAX      INTEGER (1..4094)
   MAX-ACCESS  read-write
   STATUS      current
   DESCRIPTION
       " VLAN ID, range: 1 - 4094. "
   ::= { fgs2528kxIPSourceGuardStaticEntry 3 }

fgs2528kxIPSourceGuardStaticIPAddress OBJECT-TYPE
   SYNTAX      IpAddress
   MAX-ACCESS  read-write
   STATUS      current
   DESCRIPTION
       " IP address allowed for doing IP source guard. "
   ::= { fgs2528kxIPSourceGuardStaticEntry 4 }

fgs2528kxIPSourceGuardStaticMACAddress OBJECT-TYPE
   SYNTAX      MacAddress
   MAX-ACCESS  read-write
   STATUS      current
   DESCRIPTION
       " Allowed Source MAC address, format 0a 1b 2c 3d 4e 5f "
   ::= { fgs2528kxIPSourceGuardStaticEntry 5 }

fgs2528kxIPSourceGuardStaticRowStatus OBJECT-TYPE
   SYNTAX      INTEGER (1..5)
   MAX-ACCESS  read-write
   STATUS      current
   DESCRIPTION
       "1: active
        2: notInservice
        3: edit
        4: destroy
        5: undo"
   ::= { fgs2528kxIPSourceGuardStaticEntry 6 }

fgs2528kxIPSourceGuardDynamicTable OBJECT-TYPE
   SYNTAX      SEQUENCE OF FGS2528KXIPSourceGuardDynamicEntry
   MAX-ACCESS  not-accessible
   STATUS      current
   DESCRIPTION
       " "
   ::= { fgs2528kxIPSourceGuard 3 }

fgs2528kxIPSourceGuardDynamicEntry OBJECT-TYPE
   SYNTAX      FGS2528KXIPSourceGuardDynamicEntry
   MAX-ACCESS  not-accessible
   STATUS      current
   DESCRIPTION
       ""
   INDEX    { fgs2528kxIPSourceGuardDynamicIndex  }
   ::= { fgs2528kxIPSourceGuardDynamicTable 1 }

FGS2528KXIPSourceGuardDynamicEntry ::= SEQUENCE {
   fgs2528kxIPSourceGuardDynamicIndex          INTEGER,
   fgs2528kxIPSourceGuardDynamicPort           INTEGER,
   fgs2528kxIPSourceGuardDynamicVLANId         INTEGER,
   fgs2528kxIPSourceGuardDynamicIPAddress      IpAddress,
   fgs2528kxIPSourceGuardDynamicMACAddress     MacAddress
}

fgs2528kxIPSourceGuardDynamicIndex OBJECT-TYPE
   SYNTAX      INTEGER(1..4095)
   MAX-ACCESS  not-accessible
   STATUS      current
   DESCRIPTION
       " "
   ::= { fgs2528kxIPSourceGuardDynamicEntry 1 }

fgs2528kxIPSourceGuardDynamicPort OBJECT-TYPE
   SYNTAX      INTEGER (1..10)
   MAX-ACCESS  read-only
   STATUS      current
   DESCRIPTION
       " "
   ::= { fgs2528kxIPSourceGuardDynamicEntry 2 }

fgs2528kxIPSourceGuardDynamicVLANId OBJECT-TYPE
   SYNTAX      INTEGER (1..4094)
   MAX-ACCESS  read-only
   STATUS      current
   DESCRIPTION
       " "
   ::= { fgs2528kxIPSourceGuardDynamicEntry 3 }

fgs2528kxIPSourceGuardDynamicIPAddress OBJECT-TYPE
   SYNTAX      IpAddress
   MAX-ACCESS  read-only
   STATUS      current
   DESCRIPTION
       " "
   ::= { fgs2528kxIPSourceGuardDynamicEntry 4 }

fgs2528kxIPSourceGuardDynamicMACAddress OBJECT-TYPE
   SYNTAX      MacAddress
   MAX-ACCESS  read-only
   STATUS      current
   DESCRIPTION
       " "
   ::= { fgs2528kxIPSourceGuardDynamicEntry 5 }

fgs2528kxARPInspection                                         OBJECT IDENTIFIER ::= { fgs2528kxSecurity 2 }

fgs2528kxARPInspectionConf                                     OBJECT IDENTIFIER ::= { fgs2528kxARPInspection 1 }

fgs2528kxARPInspectionConfMode OBJECT-TYPE
   SYNTAX      INTEGER(0|1)
   MAX-ACCESS  read-write
   STATUS      current
   DESCRIPTION
       "default: 0
        0: disable
        1: enable"
   ::= { fgs2528kxARPInspectionConf 1 }

fgs2528kxARPInspectionConfTable OBJECT-TYPE
   SYNTAX      SEQUENCE OF FGS2528KXARPInspectionConfEntry
   MAX-ACCESS  not-accessible
   STATUS      current
   DESCRIPTION
       " "
   ::= { fgs2528kxARPInspectionConf 2 }

fgs2528kxARPInspectionConfEntry OBJECT-TYPE
   SYNTAX      FGS2528KXARPInspectionConfEntry
   MAX-ACCESS  not-accessible
   STATUS      current
   DESCRIPTION
       ""
   INDEX    { fgs2528kxARPInspectionConfPortIndex  }
   ::= { fgs2528kxARPInspectionConfTable 1 }

FGS2528KXARPInspectionConfEntry ::= SEQUENCE {
   fgs2528kxARPInspectionConfPortIndex	INTEGER,
   fgs2528kxARPInspectionConfPortMode	INTEGER
}

fgs2528kxARPInspectionConfPortIndex OBJECT-TYPE
   SYNTAX      INTEGER(1..4095)
   MAX-ACCESS  not-accessible
   STATUS      current
   DESCRIPTION
       " "
   ::= { fgs2528kxARPInspectionConfEntry 1 }

fgs2528kxARPInspectionConfPortMode OBJECT-TYPE
   SYNTAX      INTEGER (0|1)
   MAX-ACCESS  read-write
   STATUS      current
   DESCRIPTION
       "default: 0
        0: disable
        1: enable"
   ::= { fgs2528kxARPInspectionConfEntry 2 }


fgs2528kxARPInspectionStatic                                OBJECT IDENTIFIER ::= { fgs2528kxARPInspection 2 }

fgs2528kxARPInspectionStaticCreate OBJECT-TYPE
   SYNTAX      INTEGER (0|1)
   MAX-ACCESS  read-write
   STATUS      current
   DESCRIPTION
       "default: 0
        0: none
        1: create"
   ::= { fgs2528kxARPInspectionStatic 1 }

fgs2528kxARPInspectionStaticTable OBJECT-TYPE
   SYNTAX      SEQUENCE OF FGS2528KXARPInspectionStaticEntry
   MAX-ACCESS  not-accessible
   STATUS      current
   DESCRIPTION
       " "
   ::= { fgs2528kxARPInspectionStatic 2 }

fgs2528kxARPInspectionStaticEntry OBJECT-TYPE
   SYNTAX      FGS2528KXARPInspectionStaticEntry
   MAX-ACCESS  not-accessible
   STATUS      current
   DESCRIPTION
       ""
   INDEX    { fgs2528kxARPInspectionStaticIndex  }
   ::= { fgs2528kxARPInspectionStaticTable 1 }

FGS2528KXARPInspectionStaticEntry ::= SEQUENCE {
   fgs2528kxARPInspectionStaticIndex       INTEGER,
   fgs2528kxARPInspectionStaticPort        INTEGER,
   fgs2528kxARPInspectionStaticVLANId      INTEGER,
   fgs2528kxARPInspectionStaticIPAddress   IpAddress,
   fgs2528kxARPInspectionStaticMACAddress  MacAddress,
   fgs2528kxARPInspectionStaticRowStatus   INTEGER
}

fgs2528kxARPInspectionStaticIndex OBJECT-TYPE
   SYNTAX      INTEGER(1..4095)
   MAX-ACCESS  not-accessible
   STATUS      current
   DESCRIPTION
       ""
   ::= { fgs2528kxARPInspectionStaticEntry 1 }

fgs2528kxARPInspectionStaticPort OBJECT-TYPE
   SYNTAX      INTEGER(1..4095)
   MAX-ACCESS  read-write
   STATUS      current
   DESCRIPTION
       " Port, range: 1 - port number. "
   ::= { fgs2528kxARPInspectionStaticEntry 2 }

fgs2528kxARPInspectionStaticVLANId OBJECT-TYPE
   SYNTAX      INTEGER (1..4094)
   MAX-ACCESS  read-write
   STATUS      current
   DESCRIPTION
       " VLAN ID, range: 1 - 4094. "
   ::= { fgs2528kxARPInspectionStaticEntry 3 }

fgs2528kxARPInspectionStaticIPAddress OBJECT-TYPE
   SYNTAX      IpAddress
   MAX-ACCESS  read-write
   STATUS      current
   DESCRIPTION
       " IP address allowed for doing ARP request. "
   ::= { fgs2528kxARPInspectionStaticEntry 4 }

fgs2528kxARPInspectionStaticMACAddress OBJECT-TYPE
   SYNTAX      MacAddress
   MAX-ACCESS  read-write
   STATUS      current
   DESCRIPTION
       " Allowed Source MAC address in ARP request packets, format 0a 1b 2c 3d 4e 5f "
   ::= { fgs2528kxARPInspectionStaticEntry 5 }

fgs2528kxARPInspectionStaticRowStatus OBJECT-TYPE
   SYNTAX      INTEGER(1..5)
   MAX-ACCESS  read-write
   STATUS      current
   DESCRIPTION
       "1: active
        2: notInservice
        3: edit
        4: destroy
        5: undo"
   ::= { fgs2528kxARPInspectionStaticEntry 6 }

fgs2528kxARPInspectionDynamicTable OBJECT-TYPE
   SYNTAX      SEQUENCE OF FGS2528KXARPInspectionDynamicEntry
   MAX-ACCESS  not-accessible
   STATUS      current
   DESCRIPTION
       " "
   ::= { fgs2528kxARPInspection 3 }

fgs2528kxARPInspectionDynamicEntry OBJECT-TYPE
   SYNTAX      FGS2528KXARPInspectionDynamicEntry
   MAX-ACCESS  not-accessible
   STATUS      current
   DESCRIPTION
       ""
   INDEX    { fgs2528kxARPInspectionDynamicIndex  }
   ::= { fgs2528kxARPInspectionDynamicTable 1 }

FGS2528KXARPInspectionDynamicEntry ::= SEQUENCE {
   fgs2528kxARPInspectionDynamicIndex          INTEGER,
   fgs2528kxARPInspectionDynamicPort           INTEGER,
   fgs2528kxARPInspectionDynamicVLANId         INTEGER,
   fgs2528kxARPInspectionDynamicIPAddress      IpAddress,
   fgs2528kxARPInspectionDynamicMACAddress     MacAddress
}

fgs2528kxARPInspectionDynamicIndex OBJECT-TYPE
   SYNTAX      INTEGER(1..4095)
   MAX-ACCESS  not-accessible
   STATUS      current
   DESCRIPTION
       " "
   ::= { fgs2528kxARPInspectionDynamicEntry 1 }

fgs2528kxARPInspectionDynamicPort OBJECT-TYPE
   SYNTAX      INTEGER(1..4095)
   MAX-ACCESS  read-only
   STATUS      current
   DESCRIPTION
       ""
   ::= { fgs2528kxARPInspectionDynamicEntry 2 }

fgs2528kxARPInspectionDynamicVLANId OBJECT-TYPE
   SYNTAX      INTEGER (1..4094)
   MAX-ACCESS  read-only
   STATUS      current
   DESCRIPTION
       ""
   ::= { fgs2528kxARPInspectionDynamicEntry 3 }

fgs2528kxARPInspectionDynamicIPAddress OBJECT-TYPE
   SYNTAX      IpAddress
   MAX-ACCESS  read-only
   STATUS      current
   DESCRIPTION
       ""
   ::= { fgs2528kxARPInspectionDynamicEntry 4 }

fgs2528kxARPInspectionDynamicMACAddress OBJECT-TYPE
   SYNTAX      MacAddress
   MAX-ACCESS  read-only
   STATUS      current
   DESCRIPTION
       ""
   ::= { fgs2528kxARPInspectionDynamicEntry 5 }

fgs2528kxDHCPSnooping                                          OBJECT IDENTIFIER ::= { fgs2528kxSecurity 3 }

fgs2528kxDHCPSnoopingConf                                          OBJECT IDENTIFIER ::= { fgs2528kxDHCPSnooping 1 }

fgs2528kxDHCPSnoopingMode OBJECT-TYPE
   SYNTAX      INTEGER(0|1)
   MAX-ACCESS  read-write
   STATUS      current
   DESCRIPTION
       "default: 0
       0: disable
       1: enable"
   ::= { fgs2528kxDHCPSnoopingConf 1 }

fgs2528kxDHCPSnoopingPortModeConfigurationTable OBJECT-TYPE
   SYNTAX      SEQUENCE OF FGS2528KXDHCPSnoopingPortModeConfigurationEntry
   MAX-ACCESS  not-accessible
   STATUS      current
   DESCRIPTION
       " "
   ::= { fgs2528kxDHCPSnoopingConf 2 }

fgs2528kxDHCPSnoopingPortModeConfigurationEntry OBJECT-TYPE
   SYNTAX      FGS2528KXDHCPSnoopingPortModeConfigurationEntry
   MAX-ACCESS  not-accessible
   STATUS      current
   DESCRIPTION
       ""
   INDEX    { fgs2528kxDHCPSnoopingPortModeConfigurationPort  }
   ::= { fgs2528kxDHCPSnoopingPortModeConfigurationTable 1 }

FGS2528KXDHCPSnoopingPortModeConfigurationEntry ::= SEQUENCE {
   fgs2528kxDHCPSnoopingPortModeConfigurationPort	INTEGER,
   fgs2528kxDHCPSnoopingPortModeConfigurationMode	INTEGER
}

fgs2528kxDHCPSnoopingPortModeConfigurationPort OBJECT-TYPE
   SYNTAX      INTEGER(1..4095)
   MAX-ACCESS  not-accessible
   STATUS      current
   DESCRIPTION
       " "
   ::= { fgs2528kxDHCPSnoopingPortModeConfigurationEntry 1 }

fgs2528kxDHCPSnoopingPortModeConfigurationMode OBJECT-TYPE
   SYNTAX      INTEGER (0|1)
   MAX-ACCESS  read-write
   STATUS      current
   DESCRIPTION
       "default: 1
       0: trust port mode
       1: untrust port mode"
   ::= { fgs2528kxDHCPSnoopingPortModeConfigurationEntry 2 }

fgs2528kxDHCPSnoopingStatisticsTable OBJECT-TYPE
   SYNTAX      SEQUENCE OF FGS2528KXDHCPSnoopingStatisticsEntry
   MAX-ACCESS  not-accessible
   STATUS      current
   DESCRIPTION
       " "
   ::= { fgs2528kxDHCPSnooping 2 }

fgs2528kxDHCPSnoopingStatisticsEntry OBJECT-TYPE
   SYNTAX      FGS2528KXDHCPSnoopingStatisticsEntry
   MAX-ACCESS  not-accessible
   STATUS      current
   DESCRIPTION
       ""
   INDEX    { fgs2528kxDHCPSnoopingStatisticsPort  }
   ::= { fgs2528kxDHCPSnoopingStatisticsTable 1 }

FGS2528KXDHCPSnoopingStatisticsEntry ::= SEQUENCE {
   fgs2528kxDHCPSnoopingStatisticsPort         INTEGER,
   fgs2528kxDHCPSnoopingStatisticsClear        INTEGER,
   fgs2528kxDHCPSnoopingRxDiscover             Counter32,
   fgs2528kxDHCPSnoopingRxOffer                Counter32,
   fgs2528kxDHCPSnoopingRxRequest              Counter32,
   fgs2528kxDHCPSnoopingRxDecline              Counter32,
   fgs2528kxDHCPSnoopingRxACK                  Counter32,
   fgs2528kxDHCPSnoopingRxNAK                  Counter32,
   fgs2528kxDHCPSnoopingRxRelease              Counter32,
   fgs2528kxDHCPSnoopingRxInform               Counter32,
   fgs2528kxDHCPSnoopingRxLeaseQuery           Counter32,
   fgs2528kxDHCPSnoopingRxLeaseUnassigned      Counter32,
   fgs2528kxDHCPSnoopingRxLeaseUnknown         Counter32,
   fgs2528kxDHCPSnoopingRxLeaseActive          Counter32,
   fgs2528kxDHCPSnoopingTxDiscover             Counter32,
   fgs2528kxDHCPSnoopingTxOffer                Counter32,
   fgs2528kxDHCPSnoopingTxRequest              Counter32,
   fgs2528kxDHCPSnoopingTxDecline              Counter32,
   fgs2528kxDHCPSnoopingTxACK                  Counter32,
   fgs2528kxDHCPSnoopingTxNAK                  Counter32,
   fgs2528kxDHCPSnoopingTxRelease              Counter32,
   fgs2528kxDHCPSnoopingTxInform               Counter32,
   fgs2528kxDHCPSnoopingTxLeaseQuery           Counter32,
   fgs2528kxDHCPSnoopingTxLeaseUnassigned      Counter32,
   fgs2528kxDHCPSnoopingTxLeaseUnknown         Counter32,
   fgs2528kxDHCPSnoopingTxLeaseActive          Counter32
}

fgs2528kxDHCPSnoopingStatisticsPort OBJECT-TYPE
   SYNTAX      INTEGER(1..4095)
   MAX-ACCESS  not-accessible
   STATUS      current
   DESCRIPTION
       " "
   ::= { fgs2528kxDHCPSnoopingStatisticsEntry 1 }

fgs2528kxDHCPSnoopingStatisticsClear OBJECT-TYPE
   SYNTAX      INTEGER (0|1)
   MAX-ACCESS  read-write
   STATUS      current
   DESCRIPTION
       "default: 0
       0: none
       1: clear"
   ::= { fgs2528kxDHCPSnoopingStatisticsEntry 2 }

fgs2528kxDHCPSnoopingRxDiscover OBJECT-TYPE
   SYNTAX      Counter32
   MAX-ACCESS  read-only
   STATUS      current
   DESCRIPTION
       " "
   ::= { fgs2528kxDHCPSnoopingStatisticsEntry 3 }

fgs2528kxDHCPSnoopingRxOffer OBJECT-TYPE
   SYNTAX      Counter32
   MAX-ACCESS  read-only
   STATUS      current
   DESCRIPTION
       " "
   ::= { fgs2528kxDHCPSnoopingStatisticsEntry 4 }

fgs2528kxDHCPSnoopingRxRequest OBJECT-TYPE
   SYNTAX      Counter32
   MAX-ACCESS  read-only
   STATUS      current
   DESCRIPTION
       " "
   ::= { fgs2528kxDHCPSnoopingStatisticsEntry 5 }

fgs2528kxDHCPSnoopingRxDecline OBJECT-TYPE
   SYNTAX      Counter32
   MAX-ACCESS  read-only
   STATUS      current
   DESCRIPTION
       " "
   ::= { fgs2528kxDHCPSnoopingStatisticsEntry 6 }

fgs2528kxDHCPSnoopingRxACK OBJECT-TYPE
   SYNTAX      Counter32
   MAX-ACCESS  read-only
   STATUS      current
   DESCRIPTION
       " "
   ::= { fgs2528kxDHCPSnoopingStatisticsEntry 7 }

fgs2528kxDHCPSnoopingRxNAK OBJECT-TYPE
   SYNTAX      Counter32
   MAX-ACCESS  read-only
   STATUS      current
   DESCRIPTION
       " "
   ::= { fgs2528kxDHCPSnoopingStatisticsEntry 8 }

fgs2528kxDHCPSnoopingRxRelease OBJECT-TYPE
   SYNTAX      Counter32
   MAX-ACCESS  read-only
   STATUS      current
   DESCRIPTION
       " "
   ::= { fgs2528kxDHCPSnoopingStatisticsEntry 9 }

fgs2528kxDHCPSnoopingRxInform OBJECT-TYPE
   SYNTAX      Counter32
   MAX-ACCESS  read-only
   STATUS      current
   DESCRIPTION
       " "
   ::= { fgs2528kxDHCPSnoopingStatisticsEntry 10 }

fgs2528kxDHCPSnoopingRxLeaseQuery OBJECT-TYPE
   SYNTAX      Counter32
   MAX-ACCESS  read-only
   STATUS      current
   DESCRIPTION
       " "
   ::= { fgs2528kxDHCPSnoopingStatisticsEntry 11 }

fgs2528kxDHCPSnoopingRxLeaseUnassigned OBJECT-TYPE
   SYNTAX      Counter32
   MAX-ACCESS  read-only
   STATUS      current
   DESCRIPTION
       " "
   ::= { fgs2528kxDHCPSnoopingStatisticsEntry 12 }

fgs2528kxDHCPSnoopingRxLeaseUnknown OBJECT-TYPE
   SYNTAX      Counter32
   MAX-ACCESS  read-only
   STATUS      current
   DESCRIPTION
       " "
   ::= { fgs2528kxDHCPSnoopingStatisticsEntry 13 }

fgs2528kxDHCPSnoopingRxLeaseActive OBJECT-TYPE
   SYNTAX      Counter32
   MAX-ACCESS  read-only
   STATUS      current
   DESCRIPTION
       " "
   ::= { fgs2528kxDHCPSnoopingStatisticsEntry 14 }

fgs2528kxDHCPSnoopingTxDiscover OBJECT-TYPE
   SYNTAX      Counter32
   MAX-ACCESS  read-only
   STATUS      current
   DESCRIPTION
       " "
   ::= { fgs2528kxDHCPSnoopingStatisticsEntry 15 }

fgs2528kxDHCPSnoopingTxOffer OBJECT-TYPE
   SYNTAX      Counter32
   MAX-ACCESS  read-only
   STATUS      current
   DESCRIPTION
       " "
   ::= { fgs2528kxDHCPSnoopingStatisticsEntry 16 }

fgs2528kxDHCPSnoopingTxRequest OBJECT-TYPE
   SYNTAX      Counter32
   MAX-ACCESS  read-only
   STATUS      current
   DESCRIPTION
       " "
   ::= { fgs2528kxDHCPSnoopingStatisticsEntry 17 }

fgs2528kxDHCPSnoopingTxDecline OBJECT-TYPE
   SYNTAX      Counter32
   MAX-ACCESS  read-only
   STATUS      current
   DESCRIPTION
       " "
   ::= { fgs2528kxDHCPSnoopingStatisticsEntry 18 }

fgs2528kxDHCPSnoopingTxACK OBJECT-TYPE
   SYNTAX      Counter32
   MAX-ACCESS  read-only
   STATUS      current
   DESCRIPTION
       " "
   ::= { fgs2528kxDHCPSnoopingStatisticsEntry 19 }

fgs2528kxDHCPSnoopingTxNAK OBJECT-TYPE
   SYNTAX      Counter32
   MAX-ACCESS  read-only
   STATUS      current
   DESCRIPTION
       " "
   ::= { fgs2528kxDHCPSnoopingStatisticsEntry 20 }

fgs2528kxDHCPSnoopingTxRelease OBJECT-TYPE
   SYNTAX      Counter32
   MAX-ACCESS  read-only
   STATUS      current
   DESCRIPTION
       " "
   ::= { fgs2528kxDHCPSnoopingStatisticsEntry 21 }

fgs2528kxDHCPSnoopingTxInform OBJECT-TYPE
   SYNTAX      Counter32
   MAX-ACCESS  read-only
   STATUS      current
   DESCRIPTION
       " "
   ::= { fgs2528kxDHCPSnoopingStatisticsEntry 22 }

fgs2528kxDHCPSnoopingTxLeaseQuery OBJECT-TYPE
   SYNTAX      Counter32
   MAX-ACCESS  read-only
   STATUS      current
   DESCRIPTION
       " "
   ::= { fgs2528kxDHCPSnoopingStatisticsEntry 23 }

fgs2528kxDHCPSnoopingTxLeaseUnassigned OBJECT-TYPE
   SYNTAX      Counter32
   MAX-ACCESS  read-only
   STATUS      current
   DESCRIPTION
       " "
   ::= { fgs2528kxDHCPSnoopingStatisticsEntry 24 }

fgs2528kxDHCPSnoopingTxLeaseUnknown OBJECT-TYPE
   SYNTAX      Counter32
   MAX-ACCESS  read-only
   STATUS      current
   DESCRIPTION
       " "
   ::= { fgs2528kxDHCPSnoopingStatisticsEntry 25 }

fgs2528kxDHCPSnoopingTxLeaseActive OBJECT-TYPE
   SYNTAX      Counter32
   MAX-ACCESS  read-only
   STATUS      current
   DESCRIPTION
       " "
   ::= { fgs2528kxDHCPSnoopingStatisticsEntry 26 }


fgs2528kxDHCPRelay                                             OBJECT IDENTIFIER ::= { fgs2528kxSecurity 4 }

fgs2528kxDHCPRelayConfiguration                                         OBJECT IDENTIFIER ::= { fgs2528kxDHCPRelay 1 }

fgs2528kxDHCPRelayMode OBJECT-TYPE
   SYNTAX      INTEGER(0|1)
   MAX-ACCESS  read-write
   STATUS      current
   DESCRIPTION
       "default: 0
       0: disable
       1: enable
       We need at least one server"
   ::= { fgs2528kxDHCPRelayConfiguration 1 }

fgs2528kxDHCPRelayServer OBJECT-TYPE
   SYNTAX      IpAddress
   MAX-ACCESS  read-write
   STATUS      current
   DESCRIPTION
       " "
   ::= { fgs2528kxDHCPRelayConfiguration 2 }

fgs2528kxDHCPRelayInformationMode OBJECT-TYPE
   SYNTAX      INTEGER(0|1)
   MAX-ACCESS  read-write
   STATUS      current
   DESCRIPTION
       "default: 0
       0: disable
       1: enable "
   ::= { fgs2528kxDHCPRelayConfiguration 3 }

fgs2528kxDHCPRelayInformationPolicy OBJECT-TYPE
   SYNTAX      INTEGER(0..2)
   MAX-ACCESS  read-write
   STATUS      current
   DESCRIPTION
       "default: 0
       0: replace
       1: keep
       2: drop "
   ::= { fgs2528kxDHCPRelayConfiguration 4 }

fgs2528kxDHCPRelayStatistics                                   OBJECT IDENTIFIER ::= { fgs2528kxDHCPRelay 2 }

fgs2528kxDHCPRelayServerStatistics                                   OBJECT IDENTIFIER ::= { fgs2528kxDHCPRelayStatistics 1 }

fgs2528kxServerStatTransmitToServer OBJECT-TYPE
   SYNTAX      Counter32
   MAX-ACCESS  read-only
   STATUS      current
   DESCRIPTION
       " "
   ::= { fgs2528kxDHCPRelayServerStatistics 1 }

fgs2528kxServerStatTransmitError OBJECT-TYPE
   SYNTAX      Counter32
   MAX-ACCESS  read-only
   STATUS      current
   DESCRIPTION
       " "
   ::= { fgs2528kxDHCPRelayServerStatistics 2 }

fgs2528kxServerStatReceiveFromServer OBJECT-TYPE
   SYNTAX      Counter32
   MAX-ACCESS  read-only
   STATUS      current
   DESCRIPTION
       " "
   ::= { fgs2528kxDHCPRelayServerStatistics 3 }

fgs2528kxServerStatReceiveMissingAgentOption OBJECT-TYPE
   SYNTAX      Counter32
   MAX-ACCESS  read-only
   STATUS      current
   DESCRIPTION
       " "
   ::= { fgs2528kxDHCPRelayServerStatistics 4 }

fgs2528kxServerStatReceiveMissingCircuitID OBJECT-TYPE
   SYNTAX      Counter32
   MAX-ACCESS  read-only
   STATUS      current
   DESCRIPTION
       " "
   ::= { fgs2528kxDHCPRelayServerStatistics 5 }

fgs2528kxServerStatReceiveMissingRemoteID OBJECT-TYPE
   SYNTAX      Counter32
   MAX-ACCESS  read-only
   STATUS      current
   DESCRIPTION
       " "
   ::= { fgs2528kxDHCPRelayServerStatistics 6 }

fgs2528kxServerStatReceiveBadCircuitID OBJECT-TYPE
   SYNTAX      Counter32
   MAX-ACCESS  read-only
   STATUS      current
   DESCRIPTION
       " "
   ::= { fgs2528kxDHCPRelayServerStatistics 7 }

fgs2528kxServerStatReceiveBadRemoteID OBJECT-TYPE
   SYNTAX      Counter32
   MAX-ACCESS  read-only
   STATUS      current
   DESCRIPTION
       " "
   ::= { fgs2528kxDHCPRelayServerStatistics 8 }

fgs2528kxDHCPRelayClientStatistics                                   OBJECT IDENTIFIER ::= { fgs2528kxDHCPRelayStatistics 2 }

fgs2528kxClientStatTransmitToClient OBJECT-TYPE
   SYNTAX      Counter32
   MAX-ACCESS  read-only
   STATUS      current
   DESCRIPTION
       " "
   ::= { fgs2528kxDHCPRelayClientStatistics 1 }

fgs2528kxClientStatTransmitError OBJECT-TYPE
   SYNTAX      Counter32
   MAX-ACCESS  read-only
   STATUS      current
   DESCRIPTION
       " "
   ::= { fgs2528kxDHCPRelayClientStatistics 2 }

fgs2528kxClientStatReceivefromClient OBJECT-TYPE
   SYNTAX      Counter32
   MAX-ACCESS  read-only
   STATUS      current
   DESCRIPTION
       " "
   ::= { fgs2528kxDHCPRelayClientStatistics 3 }

fgs2528kxClientStatReceiveAgentOption OBJECT-TYPE
   SYNTAX      Counter32
   MAX-ACCESS  read-only
   STATUS      current
   DESCRIPTION
       " "
   ::= { fgs2528kxDHCPRelayClientStatistics 4 }

fgs2528kxClientStatReplaceAgentOption OBJECT-TYPE
   SYNTAX      Counter32
   MAX-ACCESS  read-only
   STATUS      current
   DESCRIPTION
       " "
   ::= { fgs2528kxDHCPRelayClientStatistics 5 }

fgs2528kxClientStatKeepAgentOption OBJECT-TYPE
   SYNTAX      Counter32
   MAX-ACCESS  read-only
   STATUS      current
   DESCRIPTION
       " "
   ::= { fgs2528kxDHCPRelayClientStatistics 6 }

fgs2528kxClientStatDropAgentOption OBJECT-TYPE
   SYNTAX      Counter32
   MAX-ACCESS  read-only
   STATUS      current
   DESCRIPTION
       " "
   ::= { fgs2528kxDHCPRelayClientStatistics 7 }

fgs2528kxPortSecurity                                          OBJECT IDENTIFIER ::= { fgs2528kxSecurity 5 }

fgs2528kxPortSecLimitCtrl                                      OBJECT IDENTIFIER ::= { fgs2528kxPortSecurity 1 }

fgs2528kxPortSecLimitCtrlSystemConf                                      OBJECT IDENTIFIER ::= { fgs2528kxPortSecLimitCtrl 1 }

fgs2528kxPortSecurityMode OBJECT-TYPE
   SYNTAX      INTEGER(0|1)
   MAX-ACCESS  read-write
   STATUS      current
   DESCRIPTION
       "default: 0
       0: disable
       1: enable "
   ::= { fgs2528kxPortSecLimitCtrlSystemConf 1 }

fgs2528kxPortSecurityAging OBJECT-TYPE
   SYNTAX      INTEGER(0|1)
   MAX-ACCESS  read-write
   STATUS      current
   DESCRIPTION
       "default: 0
       0: disable
       1: enable "
   ::= { fgs2528kxPortSecLimitCtrlSystemConf 2 }

fgs2528kxPortSecurityAgingPeriod OBJECT-TYPE
   SYNTAX      INTEGER(10..10000000)
   MAX-ACCESS  read-write
   STATUS      current
   DESCRIPTION
       "default: 3600, range: 10-10000000 "
   ::= { fgs2528kxPortSecLimitCtrlSystemConf 3 }

fgs2528kxPortSecLimitCtrlTable OBJECT-TYPE
   SYNTAX      SEQUENCE OF FGS2528KXPortSecLimitCtrlEntry
   MAX-ACCESS  not-accessible
   STATUS      current
   DESCRIPTION
       " "
   ::= { fgs2528kxPortSecLimitCtrl 2 }

fgs2528kxPortSecLimitCtrlEntry OBJECT-TYPE
   SYNTAX      FGS2528KXPortSecLimitCtrlEntry
   MAX-ACCESS  not-accessible
   STATUS      current
   DESCRIPTION
       ""
   INDEX    { fgs2528kxPortSecLimitCtrlPort  }
   ::= { fgs2528kxPortSecLimitCtrlTable 1 }

FGS2528KXPortSecLimitCtrlEntry ::= SEQUENCE {
   fgs2528kxPortSecLimitCtrlPort        INTEGER,
   fgs2528kxPortSecLimitCtrlPortMode	INTEGER,
   fgs2528kxPortSecLimitCtrlPortLimit	INTEGER,
   fgs2528kxPortSecLimitCtrlPortAction	INTEGER,
   fgs2528kxPortSecLimitCtrlPortState	DisplayString,
   fgs2528kxPortSecLimitCtrlPortReOpen	INTEGER
}

fgs2528kxPortSecLimitCtrlPort OBJECT-TYPE
   SYNTAX      INTEGER (1..4095)
   MAX-ACCESS  not-accessible
   STATUS      current
   DESCRIPTION
       " "
   ::= { fgs2528kxPortSecLimitCtrlEntry 1 }

fgs2528kxPortSecLimitCtrlPortMode OBJECT-TYPE
   SYNTAX      INTEGER (0|1)
   MAX-ACCESS  read-write
   STATUS      current
   DESCRIPTION
       "default: 0
       0: disable
       1: enable"
   ::= { fgs2528kxPortSecLimitCtrlEntry 2 }

fgs2528kxPortSecLimitCtrlPortLimit OBJECT-TYPE
   SYNTAX      INTEGER(1..1024)
   MAX-ACCESS  read-write
   STATUS      current
   DESCRIPTION
       "default: 4, range: 1-1024"
   ::= { fgs2528kxPortSecLimitCtrlEntry 3 }

fgs2528kxPortSecLimitCtrlPortAction OBJECT-TYPE
   SYNTAX      INTEGER(0..3)
   MAX-ACCESS  read-write
   STATUS      current
   DESCRIPTION
       "default: 0
       0: none
       1: trap
       2: shutdown
       3: trap&shutdown"
   ::= { fgs2528kxPortSecLimitCtrlEntry 4 }

fgs2528kxPortSecLimitCtrlPortState OBJECT-TYPE
   SYNTAX      DisplayString
   MAX-ACCESS  read-only
   STATUS      current
   DESCRIPTION
       ""
   ::= { fgs2528kxPortSecLimitCtrlEntry 5 }

fgs2528kxPortSecLimitCtrlPortReOpen OBJECT-TYPE
   SYNTAX      INTEGER (0|1)
   MAX-ACCESS  read-write
   STATUS      current
   DESCRIPTION
       "default: 0
       0: none
       1: reopen"
   ::= { fgs2528kxPortSecLimitCtrlEntry 6 }

fgs2528kxPortSecSwitchStatusTable OBJECT-TYPE
   SYNTAX      SEQUENCE OF FGS2528KXPortSecSwitchStatusEntry
   MAX-ACCESS  not-accessible
   STATUS      current
   DESCRIPTION
       " "
   ::= { fgs2528kxPortSecurity 2 }

fgs2528kxPortSecSwitchStatusEntry OBJECT-TYPE
   SYNTAX      FGS2528KXPortSecSwitchStatusEntry
   MAX-ACCESS  not-accessible
   STATUS      current
   DESCRIPTION
       ""
   INDEX    { fgs2528kxPortSecSwitchStatusPort  }
   ::= { fgs2528kxPortSecSwitchStatusTable 1 }

FGS2528KXPortSecSwitchStatusEntry ::= SEQUENCE {
   fgs2528kxPortSecSwitchStatusPort                INTEGER,
   fgs2528kxPortSecSwitchStatusUsers               DisplayString,
   fgs2528kxPortSecSwitchStatusState               DisplayString,
   fgs2528kxPortSecSwitchStatusMACCountCurrent     INTEGER,
   fgs2528kxPortSecSwitchStatusMACCountLimit       INTEGER
}

fgs2528kxPortSecSwitchStatusPort OBJECT-TYPE
   SYNTAX      INTEGER (1..4095)
   MAX-ACCESS  not-accessible
   STATUS      current
   DESCRIPTION
       " "
   ::= { fgs2528kxPortSecSwitchStatusEntry 1 }

fgs2528kxPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { fgs2528kxPortSecSwitchStatusEntry 2 }

fgs2528kxPortSecSwitchStatusState OBJECT-TYPE
   SYNTAX      DisplayString
   MAX-ACCESS  read-only
   STATUS      current
   DESCRIPTION
       " Shows the current state of the port : Disabled, Ready, Limit Reached, Shutdown. "
   ::= { fgs2528kxPortSecSwitchStatusEntry 3 }

fgs2528kxPortSecSwitchStatusMACCountCurrent OBJECT-TYPE
   SYNTAX      INTEGER (1..4095)
   MAX-ACCESS  read-only
   STATUS      current
   DESCRIPTION
       ""
   ::= { fgs2528kxPortSecSwitchStatusEntry 4 }

fgs2528kxPortSecSwitchStatusMACCountLimit OBJECT-TYPE
   SYNTAX      INTEGER(1..4095)
   MAX-ACCESS  read-only
   STATUS      current
   DESCRIPTION
       ""
   ::= { fgs2528kxPortSecSwitchStatusEntry 5 }

fgs2528kxPortSecPortStatus                                      OBJECT IDENTIFIER ::= { fgs2528kxPortSecurity 3 }

fgs2528kxPortSecPortStatusPort OBJECT-TYPE
   SYNTAX       INTEGER (1..4095)
   MAX-ACCESS   read-write
   STATUS       current
   DESCRIPTION
       "default: 0
        0 : None"
   ::= { fgs2528kxPortSecPortStatus 1 }

fgs2528kxPortSecPortStatusTable OBJECT-TYPE
   SYNTAX      SEQUENCE OF FGS2528KXPortSecPortStatusEntry
   MAX-ACCESS  not-accessible
   STATUS      current
   DESCRIPTION
      " "
   ::= { fgs2528kxPortSecPortStatus 2 }

fgs2528kxPortSecPortStatusEntry OBJECT-TYPE
   SYNTAX      FGS2528KXPortSecPortStatusEntry
   MAX-ACCESS  not-accessible
   STATUS      current
   DESCRIPTION
       ""
   INDEX    { fgs2528kxPortSecPortStatusIndex  }
   ::= { fgs2528kxPortSecPortStatusTable 1 }

FGS2528KXPortSecPortStatusEntry ::= SEQUENCE {
   fgs2528kxPortSecPortStatusIndex              INTEGER,
   fgs2528kxPortSecPortStatusMACAddress         MacAddress,
   fgs2528kxPortSecPortStatusVLANId             INTEGER,
   fgs2528kxPortSecPortStatusState              DisplayString,
   fgs2528kxPortSecPortStatusTimeOfAddition     DisplayString,
   fgs2528kxPortSecPortStatusAgeAndHold         DisplayString
}

fgs2528kxPortSecPortStatusIndex OBJECT-TYPE
   SYNTAX      INTEGER(1..4095)
   MAX-ACCESS  not-accessible
   STATUS      current
   DESCRIPTION
       " "
   ::= { fgs2528kxPortSecPortStatusEntry 1 }

fgs2528kxPortSecPortStatusMACAddress OBJECT-TYPE
   SYNTAX      MacAddress
   MAX-ACCESS  read-only
   STATUS      current
   DESCRIPTION
       " "
   ::= { fgs2528kxPortSecPortStatusEntry 2 }

fgs2528kxPortSecPortStatusVLANId OBJECT-TYPE
   SYNTAX      INTEGER(1..4094)
   MAX-ACCESS  read-only
   STATUS      current
   DESCRIPTION
       " "
   ::= { fgs2528kxPortSecPortStatusEntry 3 }

fgs2528kxPortSecPortStatusState OBJECT-TYPE
   SYNTAX      DisplayString
   MAX-ACCESS  read-only
   STATUS      current
   DESCRIPTION
       "Blocked / Forwarding "
   ::= { fgs2528kxPortSecPortStatusEntry 4 }

fgs2528kxPortSecPortStatusTimeOfAddition OBJECT-TYPE
   SYNTAX      DisplayString
   MAX-ACCESS  read-only
   STATUS      current
   DESCRIPTION
       " "
   ::= { fgs2528kxPortSecPortStatusEntry 5 }

fgs2528kxPortSecPortStatusAgeAndHold OBJECT-TYPE
   SYNTAX      DisplayString
   MAX-ACCESS  read-only
   STATUS      current
   DESCRIPTION
       " "
   ::= { fgs2528kxPortSecPortStatusEntry 6 }


fgs2528kxAccessManagement                                      OBJECT IDENTIFIER ::= { fgs2528kxSecurity 6 }

fgs2528kxAccessMgtConf                                         OBJECT IDENTIFIER ::= { fgs2528kxAccessManagement 1 }

fgs2528kxAccessMgtConfMode OBJECT-TYPE
   SYNTAX      INTEGER(0|1)
   MAX-ACCESS  read-write
   STATUS      current
   DESCRIPTION
       "default: 0
       0: disable
       1: enable "
   ::= { fgs2528kxAccessMgtConf 1 }

fgs2528kxAccessMgtConfCreate OBJECT-TYPE
   SYNTAX      INTEGER(0|1)
   MAX-ACCESS  read-write
   STATUS      current
   DESCRIPTION
       "default: 0
       0: none
       1: create "
   ::= { fgs2528kxAccessMgtConf 2 }

fgs2528kxAccessMgtConfTable OBJECT-TYPE
   SYNTAX      SEQUENCE OF FGS2528KXAccessMgtConfEntry
   MAX-ACCESS  not-accessible
   STATUS      current
   DESCRIPTION
       " "
   ::= { fgs2528kxAccessMgtConf 3 }

fgs2528kxAccessMgtConfEntry OBJECT-TYPE
   SYNTAX      FGS2528KXAccessMgtConfEntry
   MAX-ACCESS  not-accessible
   STATUS      current
   DESCRIPTION
       ""
   INDEX    { fgs2528kxAccessMgtIndex  }
   ::= { fgs2528kxAccessMgtConfTable 1 }

FGS2528KXAccessMgtConfEntry ::= SEQUENCE {
   fgs2528kxAccessMgtIndex             INTEGER,
   fgs2528kxAccessMgtAddresstype       INTEGER,
   fgs2528kxAccessMgtStartIpAddress    DisplayString,
   fgs2528kxAccessMgtEndIpAddress      DisplayString,
   fgs2528kxAccessMgtHttpHttps         INTEGER,
   fgs2528kxAccessMgtSNMP              INTEGER,
   fgs2528kxAccessMgtTelnetSSH         INTEGER,
   fgs2528kxAccessMgtRowStatus         INTEGER
}

fgs2528kxAccessMgtIndex OBJECT-TYPE
   SYNTAX      INTEGER(1..16)
   MAX-ACCESS  read-write
   STATUS      current
   DESCRIPTION
       "Set Access Management config index
        range : 1-16."
   ::= { fgs2528kxAccessMgtConfEntry 1 }

fgs2528kxAccessMgtAddresstype OBJECT-TYPE
   SYNTAX      INTEGER(0|1)
   MAX-ACCESS  read-write
   STATUS      current
   DESCRIPTION
       "0: ipv4
       1: ipv6 "
   ::= { fgs2528kxAccessMgtConfEntry 2 }

fgs2528kxAccessMgtStartIpAddress OBJECT-TYPE
   SYNTAX      DisplayString
   MAX-ACCESS  read-write
   STATUS      current
   DESCRIPTION
       " Start IP address.
         IP address doesn't allowed all zero or all 'ff'H."
   ::= { fgs2528kxAccessMgtConfEntry 3 }

fgs2528kxAccessMgtEndIpAddress OBJECT-TYPE
   SYNTAX      DisplayString
   MAX-ACCESS  read-write
   STATUS      current
   DESCRIPTION
       " End IP address.
         IP address doesn't allowed all zero or all 'ff'H.
         End ip address is not less than start ip address."
   ::= { fgs2528kxAccessMgtConfEntry 4 }

fgs2528kxAccessMgtHttpHttps OBJECT-TYPE
   SYNTAX      INTEGER(0|1)
   MAX-ACCESS  read-write
   STATUS      current
   DESCRIPTION
       "default: 0
       0: disable
       1: enable "
   ::= { fgs2528kxAccessMgtConfEntry 5 }

fgs2528kxAccessMgtSNMP OBJECT-TYPE
   SYNTAX      INTEGER(0|1)
   MAX-ACCESS  read-write
   STATUS      current
   DESCRIPTION
       "default: 0
       0: disable
       1: enable "
   ::= { fgs2528kxAccessMgtConfEntry 6 }

fgs2528kxAccessMgtTelnetSSH OBJECT-TYPE
   SYNTAX      INTEGER(0|1)
   MAX-ACCESS  read-write
   STATUS      current
   DESCRIPTION
       "default: 0
       0: disable
       1: enable "
   ::= { fgs2528kxAccessMgtConfEntry 7 }

fgs2528kxAccessMgtRowStatus OBJECT-TYPE
   SYNTAX      INTEGER(1..5)
   MAX-ACCESS  read-write
   STATUS      current
   DESCRIPTION
       "1: active
        2: notInservice
        3: edit
        4: destroy
        5: undo"
   ::= { fgs2528kxAccessMgtConfEntry 8 }

fgs2528kxAccessMgtStatistics                                   OBJECT IDENTIFIER ::= { fgs2528kxAccessManagement 2 }

fgs2528kxHttpReceivedPkts OBJECT-TYPE
   SYNTAX      Counter32
   MAX-ACCESS  read-only
   STATUS      current
   DESCRIPTION
       " "
   ::= { fgs2528kxAccessMgtStatistics 1 }

fgs2528kxHttpAllowedPkts OBJECT-TYPE
   SYNTAX      Counter32
   MAX-ACCESS  read-only
   STATUS      current
   DESCRIPTION
       " "
   ::= { fgs2528kxAccessMgtStatistics 2 }

fgs2528kxHttpDiscardedPkts OBJECT-TYPE
   SYNTAX      Counter32
   MAX-ACCESS  read-only
   STATUS      current
   DESCRIPTION
       " "
   ::= { fgs2528kxAccessMgtStatistics 3 }

fgs2528kxHttpsReceivedPkts OBJECT-TYPE
   SYNTAX      Counter32
   MAX-ACCESS  read-only
   STATUS      current
   DESCRIPTION
       " "
   ::= { fgs2528kxAccessMgtStatistics 4 }

fgs2528kxHttpsAllowedPkts OBJECT-TYPE
   SYNTAX      Counter32
   MAX-ACCESS  read-only
   STATUS      current
   DESCRIPTION
       " "
   ::= { fgs2528kxAccessMgtStatistics 5 }

fgs2528kxHttpsDiscardedPkts OBJECT-TYPE
   SYNTAX      Counter32
   MAX-ACCESS  read-only
   STATUS      current
   DESCRIPTION
       " "
   ::= { fgs2528kxAccessMgtStatistics 6 }

fgs2528kxSnmpReceivedPkts OBJECT-TYPE
   SYNTAX      Counter32
   MAX-ACCESS  read-only
   STATUS      current
   DESCRIPTION
       " "
   ::= { fgs2528kxAccessMgtStatistics 7 }

fgs2528kxSnmpAllowedPkts OBJECT-TYPE
   SYNTAX      Counter32
   MAX-ACCESS  read-only
   STATUS      current
   DESCRIPTION
       " "
   ::= { fgs2528kxAccessMgtStatistics 8 }

fgs2528kxSnmpDiscardedPkts OBJECT-TYPE
   SYNTAX      Counter32
   MAX-ACCESS  read-only
   STATUS      current
   DESCRIPTION
       " "
   ::= { fgs2528kxAccessMgtStatistics 9 }

fgs2528kxTelnetReceivedPkts OBJECT-TYPE
   SYNTAX      Counter32
   MAX-ACCESS  read-only
   STATUS      current
   DESCRIPTION
       " "
   ::= { fgs2528kxAccessMgtStatistics 10 }

fgs2528kxTelnetAllowedPkts OBJECT-TYPE
   SYNTAX      Counter32
   MAX-ACCESS  read-only
   STATUS      current
   DESCRIPTION
       " "
   ::= { fgs2528kxAccessMgtStatistics 11 }

fgs2528kxTelnetDiscardedPkts OBJECT-TYPE
   SYNTAX      Counter32
   MAX-ACCESS  read-only
   STATUS      current
   DESCRIPTION
       " "
   ::= { fgs2528kxAccessMgtStatistics 12 }

fgs2528kxSSHReceivedPkts OBJECT-TYPE
   SYNTAX      Counter32
   MAX-ACCESS  read-only
   STATUS      current
   DESCRIPTION
       " "
   ::= { fgs2528kxAccessMgtStatistics 13 }

fgs2528kxSSHAllowedPkts OBJECT-TYPE
   SYNTAX      Counter32
   MAX-ACCESS  read-only
   STATUS      current
   DESCRIPTION
       " "
   ::= { fgs2528kxAccessMgtStatistics 14 }

fgs2528kxSSHDiscardedPkts OBJECT-TYPE
   SYNTAX      Counter32
   MAX-ACCESS  read-only
   STATUS      current
   DESCRIPTION
       " "
   ::= { fgs2528kxAccessMgtStatistics 15 }

fgs2528kxAccessMgtStatisticsClearAll OBJECT-TYPE
   SYNTAX      INTEGER(0|1)
   MAX-ACCESS  read-write
   STATUS      current
   DESCRIPTION
       "0: none
        1: clear"
   ::= { fgs2528kxAccessMgtStatistics 16 }

fgs2528kxSSH                                                   OBJECT IDENTIFIER ::= { fgs2528kxSecurity 7 }

fgs2528kxSSHMode OBJECT-TYPE
   SYNTAX      INTEGER(0|1)
   MAX-ACCESS  read-write
   STATUS      current
   DESCRIPTION
       "default: 1
        0: disable
        1: enable"
   ::= { fgs2528kxSSH 1 }

fgs2528kxHTTPS                                                 OBJECT IDENTIFIER ::= { fgs2528kxSecurity 8 }

fgs2528kxHTTPSMode OBJECT-TYPE
   SYNTAX      INTEGER(0|1)
   MAX-ACCESS  read-write
   STATUS      current
   DESCRIPTION
       "default: 1
        0: disable
        1: enable"
   ::= { fgs2528kxHTTPS 1 }

fgs2528kxHTTPSAutoRedirect OBJECT-TYPE
   SYNTAX      INTEGER(0|1)
   MAX-ACCESS  read-write
   STATUS      current
   DESCRIPTION
       "default: 0
        0: disable
        1: enable"
   ::= { fgs2528kxHTTPS 2 }

fgs2528kxAuthMethod                                            OBJECT IDENTIFIER ::= { fgs2528kxSecurity 9 }

fgs2528kxConsoleAuthMethod OBJECT-TYPE
   SYNTAX      INTEGER(0..3)
   MAX-ACCESS  read-write
   STATUS      current
   DESCRIPTION
       "default: 1
        0: none
        1: local
        2: RADIUS
        3: TACACS+"
   ::= { fgs2528kxAuthMethod 1 }

fgs2528kxConsoleFallback OBJECT-TYPE
   SYNTAX      INTEGER(0|1)
   MAX-ACCESS  read-write
   STATUS      current
   DESCRIPTION
       "default: 0
        0:disable
        1:enable"
   ::= { fgs2528kxAuthMethod 2 }

fgs2528kxTelnetAuthMethod OBJECT-TYPE
   SYNTAX      INTEGER(0..3)
   MAX-ACCESS  read-write
   STATUS      current
   DESCRIPTION
       "default: 1
        0: none
        1: local
        2: RADIUS
        3: TACACS+"
   ::= { fgs2528kxAuthMethod 3 }

fgs2528kxTelnetFallback OBJECT-TYPE
   SYNTAX      INTEGER(0|1)
   MAX-ACCESS  read-write
   STATUS      current
   DESCRIPTION
       "default: 0
        0:disable
        1:enable"
   ::= { fgs2528kxAuthMethod 4 }

fgs2528kxSshAuthMethod OBJECT-TYPE
   SYNTAX      INTEGER(0..3)
   MAX-ACCESS  read-write
   STATUS      current
   DESCRIPTION
       "default: 1
        0: none
        1: local
        2: RADIUS
        3: TACACS+"
   ::= { fgs2528kxAuthMethod 5 }

fgs2528kxSshFallback OBJECT-TYPE
   SYNTAX      INTEGER(0|1)
   MAX-ACCESS  read-write
   STATUS      current
   DESCRIPTION
       "default: 0
        0:disable
        1:enable"
   ::= { fgs2528kxAuthMethod 6 }

fgs2528kxWebAuthMethod OBJECT-TYPE
   SYNTAX      INTEGER(0..3)
   MAX-ACCESS  read-write
   STATUS      current
   DESCRIPTION
       "default: 1
        0: none
        1: local
        2: RADIUS
        3: TACACS+"
   ::= { fgs2528kxAuthMethod 7 }

fgs2528kxWebFallback OBJECT-TYPE
   SYNTAX      INTEGER(0|1)
   MAX-ACCESS  read-write
   STATUS      current
   DESCRIPTION
       "default: 0
        0:disable
        1:enable"
   ::= { fgs2528kxAuthMethod 8 }

fgs2528kxMaintenance                                           OBJECT IDENTIFIER ::= { fgs2528kxProductId 4 }

fgs2528kxRestartDevice OBJECT-TYPE
   SYNTAX      INTEGER(0|1)
   MAX-ACCESS  read-write
   STATUS      current
   DESCRIPTION
       "default: 0
        0:none
        1:yes"
   ::= { fgs2528kxMaintenance 1 }

fgs2528kxFirmware                                         OBJECT IDENTIFIER ::= { fgs2528kxMaintenance 2 }

fgs2528kxFirmwareIpAddress OBJECT-TYPE
   SYNTAX       IpAddress
   MAX-ACCESS   read-write
   STATUS       current
   DESCRIPTION
        "Get/Set the firmware tftp server."
   ::= { fgs2528kxFirmware 1 }

fgs2528kxFirmwareFileName OBJECT-TYPE
   SYNTAX       DisplayString
   MAX-ACCESS   read-write
   STATUS       current
   DESCRIPTION
        "Get/Set the path and filename for firmware upgrading."
   ::= { fgs2528kxFirmware 2 }

fgs2528kxDoFirmwareUpgrade OBJECT-TYPE
   SYNTAX       INTEGER(0|1)
   MAX-ACCESS   read-write
   STATUS       current
   DESCRIPTION
        "Do firmware upgrade. Get this OID always return zero.
              1 - do firmware upgrade.
              0 - do nothing."
   ::= { fgs2528kxFirmware 3 }

fgs2528kxSaveOrRestore                                         OBJECT IDENTIFIER ::= { fgs2528kxMaintenance 3 }

fgs2528kxFactoryDefaults OBJECT-TYPE
   SYNTAX      INTEGER(0|1)
   MAX-ACCESS  read-write
   STATUS      current
   DESCRIPTION
       "default: 0
        0:none
        1:yes"
   ::= { fgs2528kxSaveOrRestore 1 }

fgs2528kxSaveStart OBJECT-TYPE
   SYNTAX      INTEGER(0|1)
   MAX-ACCESS  read-write
   STATUS      current
   DESCRIPTION
       "default: 0
        0:none
        1:yes"
   ::= { fgs2528kxSaveOrRestore 2 }

fgs2528kxSaveUser OBJECT-TYPE
   SYNTAX      INTEGER(0|1)
   MAX-ACCESS  read-write
   STATUS      current
   DESCRIPTION
       "default: 0
        0:none
        1:yes"
   ::= { fgs2528kxSaveOrRestore 3 }

fgs2528kxRestoreUser OBJECT-TYPE
   SYNTAX      INTEGER(0|1)
   MAX-ACCESS  read-write
   STATUS      current
   DESCRIPTION
       "default: 0
        0:none
        1:yes"
   ::= { fgs2528kxSaveOrRestore 4 }


fgs2528kxExportOrImport                                        OBJECT IDENTIFIER ::= { fgs2528kxMaintenance 4 }

fgs2528kxExportIpAddress OBJECT-TYPE
   SYNTAX       IpAddress
   MAX-ACCESS   read-write
   STATUS       current
   DESCRIPTION
        "Get/Set the export tftp server."
   ::= { fgs2528kxExportOrImport 1 }

fgs2528kxExportConfigName OBJECT-TYPE
   SYNTAX       DisplayString
   MAX-ACCESS   read-write
   STATUS       current
   DESCRIPTION
       "Get/Set the export file path and name."
   ::= { fgs2528kxExportOrImport 2 }

fgs2528kxDoExportConfig OBJECT-TYPE
   SYNTAX       INTEGER(1)
   MAX-ACCESS   read-write
   STATUS       current
   DESCRIPTION
        "Do export-config.
         Get this OID always return zero.
         1 - export."
   ::= { fgs2528kxExportOrImport 3 }

fgs2528kxImportIpAddress OBJECT-TYPE
   SYNTAX       IpAddress
   MAX-ACCESS   read-write
   STATUS       current
   DESCRIPTION
        "Get/Set the import tftp server."
   ::= { fgs2528kxExportOrImport 4 }

fgs2528kxImportConfigName OBJECT-TYPE
   SYNTAX      DisplayString
   MAX-ACCESS  read-write
   STATUS      current
   DESCRIPTION
       "Get/Set the import file path and name."
   ::= { fgs2528kxExportOrImport 5 }

fgs2528kxDoImportConfig OBJECT-TYPE
   SYNTAX       INTEGER(1)
   MAX-ACCESS   read-write
   STATUS       current
   DESCRIPTION
        "Do export-config.
         Get this OID always return zero.
         1 - import."
   ::= { fgs2528kxExportOrImport 6 }

fgs2528kxDiagnostics                                           OBJECT IDENTIFIER ::= { fgs2528kxMaintenance 5 }

fgs2528kxPingIpAddress OBJECT-TYPE
   SYNTAX      IpAddress
   MAX-ACCESS  read-write
   STATUS      current
   DESCRIPTION
       " The destination IP Address. "
   ::= { fgs2528kxDiagnostics 1 }

fgs2528kxPingSize OBJECT-TYPE
   SYNTAX      INTEGER(60..1400)
   MAX-ACCESS  read-write
   STATUS      current
   DESCRIPTION
       " Size of ICMP echo packet.
         range : 60-1400, default : 64. "
   ::= { fgs2528kxDiagnostics 2 }

fgs2528kxDoPingConfig OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { fgs2528kxDiagnostics 3 }

fgs2528kxPingResult OBJECT-TYPE
   SYNTAX      DisplayString
   MAX-ACCESS  read-only
   STATUS      current
   DESCRIPTION
       " Show ping result. "
   ::= { fgs2528kxDiagnostics 4 }

fgs2528kxPing6IpAddress OBJECT-TYPE
   SYNTAX      DisplayString
   MAX-ACCESS  read-write
   STATUS      current
   DESCRIPTION
       " The destination IPv6 Address. "
   ::= { fgs2528kxDiagnostics 5 }

fgs2528kxPing6Size OBJECT-TYPE
   SYNTAX      INTEGER(60..1400)
   MAX-ACCESS  read-write
   STATUS      current
   DESCRIPTION
       " Size of ICMP echo packet.
         range : 60-1400. "
   ::= { fgs2528kxDiagnostics 6 }

fgs2528kxDoPing6Config OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { fgs2528kxDiagnostics 7 }

fgs2528kxPing6Result OBJECT-TYPE
   SYNTAX      DisplayString
   MAX-ACCESS  read-only
   STATUS      current
   DESCRIPTION
       " Show ping result. "
   ::= { fgs2528kxDiagnostics 8 }


fgs2528kxVeriPHY                                           OBJECT IDENTIFIER ::= { fgs2528kxDiagnostics 9 }

fgs2528kxVeriPHYTest OBJECT-TYPE
   SYNTAX      INTEGER (1..4095)
   MAX-ACCESS  read-write
   STATUS      current
   DESCRIPTION
       "Run VeriPHY Cable Diagnostics.
        port, range : 0 - port number.
        0 : ALL "
   ::= { fgs2528kxVeriPHY 1 }

fgs2528kxVeriPHYTable OBJECT-TYPE
   SYNTAX      SEQUENCE OF FGS2528KXVeriPHYEntry
   MAX-ACCESS  not-accessible
   STATUS      current
   DESCRIPTION
       " "
   ::= { fgs2528kxVeriPHY 2 }

fgs2528kxVeriPHYEntry OBJECT-TYPE
   SYNTAX      FGS2528KXVeriPHYEntry
   MAX-ACCESS  not-accessible
   STATUS      current
   DESCRIPTION
       ""
   INDEX    { fgs2528kxVeriPHYPort  }
   ::= { fgs2528kxVeriPHYTable 1 }

FGS2528KXVeriPHYEntry ::= SEQUENCE {
   fgs2528kxVeriPHYPort		    INTEGER,
   fgs2528kxVeriPHYPairA		DisplayString,
   fgs2528kxVeriPHYLengthA		DisplayString,
   fgs2528kxVeriPHYPairB		DisplayString,
   fgs2528kxVeriPHYLengthB		DisplayString,
   fgs2528kxVeriPHYPairC		DisplayString,
   fgs2528kxVeriPHYLengthC		DisplayString,
   fgs2528kxVeriPHYPairD		DisplayString,
   fgs2528kxVeriPHYLengthD		DisplayString
}

fgs2528kxVeriPHYPort OBJECT-TYPE
   SYNTAX      INTEGER (1..4095)
   MAX-ACCESS  not-accessible
   STATUS      current
   DESCRIPTION
       " The length (in meters) of the cable pair. "
   ::= { fgs2528kxVeriPHYEntry 1 }

fgs2528kxVeriPHYPairA OBJECT-TYPE
   SYNTAX      DisplayString
   MAX-ACCESS  read-only
   STATUS      current
   DESCRIPTION
       " The status of the cable pair. "
   ::= { fgs2528kxVeriPHYEntry 2 }

fgs2528kxVeriPHYLengthA OBJECT-TYPE
   SYNTAX      DisplayString
   MAX-ACCESS  read-only
   STATUS      current
   DESCRIPTION
       " The length (in meters) of the cable pair. "
   ::= { fgs2528kxVeriPHYEntry 3 }

fgs2528kxVeriPHYPairB OBJECT-TYPE
   SYNTAX      DisplayString
   MAX-ACCESS  read-only
   STATUS      current
   DESCRIPTION
       " The status of the cable pair. "
   ::= { fgs2528kxVeriPHYEntry 4 }

fgs2528kxVeriPHYLengthB OBJECT-TYPE
   SYNTAX      DisplayString
   MAX-ACCESS  read-only
   STATUS      current
   DESCRIPTION
       " The length (in meters) of the cable pair. "
   ::= { fgs2528kxVeriPHYEntry 5 }

fgs2528kxVeriPHYPairC OBJECT-TYPE
   SYNTAX      DisplayString
   MAX-ACCESS  read-only
   STATUS      current
   DESCRIPTION
       " The status of the cable pair. "
   ::= { fgs2528kxVeriPHYEntry 6 }

fgs2528kxVeriPHYLengthC OBJECT-TYPE
   SYNTAX      DisplayString
   MAX-ACCESS  read-only
   STATUS      current
   DESCRIPTION
       " The length (in meters) of the cable pair. "
   ::= { fgs2528kxVeriPHYEntry 7 }

fgs2528kxVeriPHYPairD OBJECT-TYPE
   SYNTAX      DisplayString
   MAX-ACCESS  read-only
   STATUS      current
   DESCRIPTION
       " The status of the cable pair. "
   ::= { fgs2528kxVeriPHYEntry 8 }

fgs2528kxVeriPHYLengthD OBJECT-TYPE
   SYNTAX      DisplayString
   MAX-ACCESS  read-only
   STATUS      current
   DESCRIPTION
       " The length (in meters) of the cable pair. "
   ::= { fgs2528kxVeriPHYEntry 9 }


------------------------------------------------------------------------------------------------------------------
fgs2528kxTrap                                                  OBJECT IDENTIFIER ::= { fgs2528kxProductId 5 }

fgs2528kxTrapEvent                                             OBJECT IDENTIFIER ::= { fgs2528kxTrap 1 }

fgs2528kxEmergency NOTIFICATION-TYPE
  OBJECTS   { fgs2528kxInformation }
  STATUS        current
    DESCRIPTION
        "The severity level is Emergency. The system is unusable."
    ::= { fgs2528kxTrapEvent 1 }

fgs2528kxAlert NOTIFICATION-TYPE
  OBJECTS   { fgs2528kxInformation }
  STATUS        current
    DESCRIPTION
        "The severity level is Alert. The action must be taken immediately."
    ::= { fgs2528kxTrapEvent 2 }

fgs2528kxCritical NOTIFICATION-TYPE
  OBJECTS   { fgs2528kxInformation }
  STATUS        current
    DESCRIPTION
        "The severity level is Critical. Critical conditions."
    ::= { fgs2528kxTrapEvent 3 }

fgs2528kxError NOTIFICATION-TYPE
  OBJECTS   { fgs2528kxInformation }
  STATUS        current
    DESCRIPTION
        "The severity level is Error. Error conditions."
    ::= { fgs2528kxTrapEvent 4 }

fgs2528kxWarning NOTIFICATION-TYPE
  OBJECTS   { fgs2528kxInformation }
  STATUS        current
    DESCRIPTION
        "The severity level is Warning. Warning conditions."
    ::= { fgs2528kxTrapEvent 5 }

fgs2528kxNotice NOTIFICATION-TYPE
  OBJECTS   { fgs2528kxInformation }
  STATUS        current
    DESCRIPTION
        "The severity level is Notice. Normal but significant condition."
    ::= { fgs2528kxTrapEvent 6 }

fgs2528kxInformational NOTIFICATION-TYPE
  OBJECTS   { fgs2528kxInformation }
  STATUS        current
    DESCRIPTION
        "The severity level is Informational. Informational messages."
    ::= { fgs2528kxTrapEvent 7 }

fgs2528kxDebug NOTIFICATION-TYPE
  OBJECTS   { fgs2528kxInformation }
  STATUS        current
    DESCRIPTION
        "The severity level is Debug. debug-level messages."
    ::= { fgs2528kxTrapEvent 8 }

fgs2528kxTrapVariable                                          OBJECT IDENTIFIER ::= { fgs2528kxTrap 2 }

fgs2528kxInformation OBJECT-TYPE
    SYNTAX      DisplayString
    MAX-ACCESS  read-only
    STATUS      current
    DESCRIPTION
        "Trap information."
    ::= { fgs2528kxTrapVariable 1 }


END
