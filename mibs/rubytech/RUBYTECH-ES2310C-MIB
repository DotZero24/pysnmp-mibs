RUBYTECH-ES2310C-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    ifIndex    FROM RFC1213-MIB;

-- @ENTERPRISE-SECTION-START
rubytech MODULE-IDENTITY
        LAST-UPDATED "200606160000Z"
        ORGANIZATION "Ruby Tech Corp."
        CONTACT-INFO
            "2F, No.7, Lane 50, Nan Kang Road, Sec.3, Taipei, Taiwan
             Email: rubytech@mail.rubytech.com.tw
             TEL: 886-2-2785-3961
             FAX: 886-2-2786-3012"
        DESCRIPTION
            "The MIB module for Ruby Tech."
        ::= { enterprises 5205 }

switch               OBJECT IDENTIFIER ::= { rubytech 2 }

es2310cProductID            OBJECT IDENTIFIER ::= { switch 23 }
-- @ENTERPRISE-SECTION-END

es2310cProduces            OBJECT IDENTIFIER ::= { es2310cProductID 1 }

es2310cSystem               OBJECT IDENTIFIER ::= { es2310cProduces 1 }

es2310cCommonSys            OBJECT IDENTIFIER ::= { es2310cSystem 1 }

es2310cReboot OBJECT-TYPE
    SYNTAX      INTEGER(0|1|2)
    MAX-ACCESS      read-write
    STATUS      current
    DESCRIPTION
        "reboot the system. Get this oid always return zero.
            0 - do nothing
            1 - reboot without saving start
            2 - reboot with saving start"
    ::= { es2310cCommonSys 1 }

es2310cBiosVsersion OBJECT-TYPE
    SYNTAX      DisplayString
    MAX-ACCESS      read-only
    STATUS      current
    DESCRIPTION
        "Get the BIOS version of the system."
    ::= { es2310cCommonSys 2 }

es2310cFirmwareVersion  OBJECT-TYPE
    SYNTAX      DisplayString
    MAX-ACCESS      read-only
    STATUS      current
    DESCRIPTION
        "Get the firmware version of the system."
    ::= { es2310cCommonSys 3 }

es2310cHardwareVersion  OBJECT-TYPE
    SYNTAX      DisplayString
    MAX-ACCESS      read-only
    STATUS      current
    DESCRIPTION
        "Get the hardware version of the system."
    ::= { es2310cCommonSys 4 }

es2310cMechanicalVersion OBJECT-TYPE
    SYNTAX      DisplayString
    MAX-ACCESS      read-only
    STATUS      current
    DESCRIPTION
        "Get the mechanical version of the system."
    ::= { es2310cCommonSys 5 }

es2310cSerialNumber OBJECT-TYPE
    SYNTAX      DisplayString
    MAX-ACCESS      read-only
    STATUS      current
    DESCRIPTION
        "Get the serial number of the system."
    ::= { es2310cCommonSys 6 }

es2310cHostMacAddress   OBJECT-TYPE
    SYNTAX      DisplayString
    MAX-ACCESS      read-only
    STATUS      current
    DESCRIPTION
        "Get the MAC address of the system."
    ::= { es2310cCommonSys 7 }

es2310cDevicePort   OBJECT-TYPE
    SYNTAX      DisplayString
    MAX-ACCESS      read-only
    STATUS      current
    DESCRIPTION
        "Get the quantity of ports that this system owns now."
    ::= { es2310cCommonSys 8 }

es2310cRamSize  OBJECT-TYPE
    SYNTAX      DisplayString
    MAX-ACCESS      read-only
    STATUS      current
    DESCRIPTION
        "Get the RAM size of the system."
    ::= { es2310cCommonSys 9 }

es2310cFlashSize  OBJECT-TYPE
    SYNTAX      DisplayString
    MAX-ACCESS      read-only
    STATUS      current
    DESCRIPTION
        "Get the flash size of the system."
    ::= { es2310cCommonSys 10 }

es2310cSystemDescription  OBJECT-TYPE
    SYNTAX      DisplayString
    MAX-ACCESS      read-only
    STATUS      current
    DESCRIPTION
        "Get the system description."
    ::= { es2310cCommonSys 11 }

es2310cDeviceName  OBJECT-TYPE
    SYNTAX      DisplayString
    MAX-ACCESS      read-write
    STATUS      current
    DESCRIPTION
        "Get/Set the device Name."
    ::= { es2310cCommonSys 12 }

es2310cIP               OBJECT IDENTIFIER ::= { es2310cSystem 2 }

es2310cDhcpSetting OBJECT-TYPE
    SYNTAX          INTEGER(0|1)
    MAX-ACCESS          read-write
    STATUS          current
    DESCRIPTION
        "Get/Set DHCP status of the system.
            0 - DHCP disable
            1 - DHCP enable"
    ::= { es2310cIP 1 }

es2310cIPAddress OBJECT-TYPE
    SYNTAX      IpAddress
    MAX-ACCESS      read-write
    STATUS      current
    DESCRIPTION
        "Get/Set the IP address of the system.
         Can't Set this OID if DHCP status is enabled."
    ::= { es2310cIP 2 }

es2310cNetMask OBJECT-TYPE
    SYNTAX      IpAddress
    MAX-ACCESS      read-write
    STATUS      current
    DESCRIPTION
        "Get/Set the netmask of the system.
         Can't Set this OID if DHCP status is enabled."
    ::= { es2310cIP 3 }

es2310cDefaultGateway OBJECT-TYPE
    SYNTAX      IpAddress
    MAX-ACCESS      read-write
    STATUS      current
    DESCRIPTION
        "Get/Set the default gateway of the system.
         Can't Set this OID if DHCP status is enabled."
    ::= { es2310cIP 4 }

es2310cDnsSetting OBJECT-TYPE
    SYNTAX      INTEGER(0|1)
    MAX-ACCESS      read-write
    STATUS      current
    DESCRIPTION
        "Get/Set the source of DNS server.
         Can't Set this OID if DHCP status is disabled.
            0 - manual, the DNS server is from manual setting
            1 - auto, the DNS server is assigned by DHCP server."
    ::= { es2310cIP 5 }

es2310cDnsServer OBJECT-TYPE
    SYNTAX      IpAddress
    MAX-ACCESS      read-write
    STATUS      current
    DESCRIPTION
        "Get/Set the DNS server of the system."
    ::= { es2310cIP 6 }

es2310cTime             OBJECT IDENTIFIER ::= { es2310cSystem 3 }

es2310cSystemCurrentTime OBJECT-TYPE
    SYNTAX      DisplayString
    MAX-ACCESS      read-only
    STATUS      current
    DESCRIPTION
        "Get the current time in the system."
    ::= { es2310cTime 1 }

es2310cManualTimeSetting OBJECT-TYPE
    SYNTAX      DisplayString
    MAX-ACCESS      read-write
    STATUS      current
    DESCRIPTION
        "Get/Set the system time of the device.
        The input format is 'Year/Month/Day/Hour/Minute/Second'.
        ex: 2004/1/1/12/34/25  means 2004/1/1 - 12:24:25 .
        value range:
        Year    : 2000 - 2036,
        Mouth   : 1 - 12,
        Day     : 1 - 31,
        Hour    : 0 - 23,
        Minute  : 0 - 59,
        sec     : 0 - 59."
    ::= { es2310cTime 2 }

es2310cNTPServer OBJECT-TYPE
    SYNTAX      DisplayString
    MAX-ACCESS      read-write
    STATUS      current
    DESCRIPTION
        "Get/Set the NTP Time Server. You can use the IP address or domain name."
    ::= { es2310cTime 3 }

es2310cNTPTimeZone OBJECT-TYPE
    SYNTAX      INTEGER(-12..13)
    MAX-ACCESS      read-write
    STATUS      current
    DESCRIPTION
        "Get/Set the NTP Time Zone.
        value range is between -12 and 13
        -12 - GMT -12:00,
        -11 - GMT -11:00,
        -10 - GMT -10:00,
         -9 - GMT -09:00,
         -8 - GMT -08:00,
         -7 - GMT -07:00,
         -6 - GMT -06:00,
         -5 - GMT -05:00,
         -4 - GMT -04:00,
         -3 - GMT -03:00,
         -2 - GMT -02:00,
         -1 - GMT -01:00,
          0 - GMT +00:00,
          1 - GMT +01:00,
          2 - GMT +02:00,
          3 - GMT +03:00,
          4 - GMT +04:00,
          5 - GMT +05:00,
          6 - GMT +06:00,
          7 - GMT +07:00,
          8 - GMT +08:00,
          9 - GMT +09:00,
         10 - GMT +10:00,
         11 - GMT +11:00,
         12 - GMT +12:00,
         13 - GMT +13:00. "
    ::= { es2310cTime 4 }

es2310cNTPTimeSync OBJECT-TYPE
    SYNTAX      INTEGER(0|1)
    MAX-ACCESS      read-write
    STATUS      current
    DESCRIPTION
        "Sync time from NTP Server. Get this oid always return zero.
        Setting the Time Server and Time Zone before doing time sync.
        Notice that time server must be correct!
        value range (1|0):
        1 - sync.
        0 - do nothing."
    ::= { es2310cTime 5 }

es2310cDaylightSavingTime OBJECT-TYPE
    SYNTAX      INTEGER(-5..5)
    MAX-ACCESS      read-write
    STATUS      current
    DESCRIPTION
        "Get/Set the daylight saving time.
        value range is between -5 and 5. unit: hour. "
    ::= { es2310cTime 6 }

es2310cDaylightStartTime OBJECT-TYPE
    SYNTAX      DisplayString
    MAX-ACCESS      read-write
    STATUS      current
    DESCRIPTION
        "Get/Set the Start time of Daylight Saving.
        The input format is 'MM/DD/HH',
        and daylight saving start month can't equal end month.
        example: month/day/hour   10/01/00
        month: 01~12, day: 01~31, hour: 00~23 ."
    ::= { es2310cTime 7 }

es2310cDaylightEndTime OBJECT-TYPE
    SYNTAX      DisplayString
    MAX-ACCESS      read-write
    STATUS      current
    DESCRIPTION
        "Get/Set the End time of Daylight Saving.
        The input format is 'MM/DD/HH',
        and daylight saving start month can't equal end month.
        example: month/day/hour   04/01/00
        month: 01~12, day: 01~31, hour: 00~23 ."
    ::= { es2310cTime 8 }

es2310cAccount              OBJECT IDENTIFIER ::= { es2310cSystem 4 }

es2310cAccountNumber OBJECT-TYPE
    SYNTAX      INTEGER(1..5)
    MAX-ACCESS      read-only
    STATUS      current
    DESCRIPTION
        "Get the current account number(s) of the system."
    ::= { es2310cAccount 1 }

es2310cAccountTable OBJECT-TYPE
    SYNTAX      SEQUENCE OF ES2310CAccountEntry
    MAX-ACCESS  not-accessible
    STATUS      current
    DESCRIPTION
        "A list of es2310cAccountEntry. The number of entries are given by
        the value of es2310cAccountNumber."
    ::= { es2310cAccount 2 }

es2310cAccountEntry OBJECT-TYPE
    SYNTAX      ES2310CAccountEntry
    MAX-ACCESS      not-accessible
    STATUS      current
    DESCRIPTION
        "Entry(s) for account information."
    INDEX {es2310cAccountIndex}
    ::= { es2310cAccountTable 1 }

ES2310CAccountEntry ::=
SEQUENCE {
    es2310cAccountIndex         INTEGER,
    es2310cAccountAuthorization DisplayString,
    es2310cAccountName             DisplayString,
    es2310cAccountPassword         DisplayString
}

es2310cAccountIndex OBJECT-TYPE
    SYNTAX      INTEGER(1..5)
    MAX-ACCESS      read-only
    STATUS      current
    DESCRIPTION
        "The index of the account entry."
    ::= { es2310cAccountEntry 1 }

es2310cAccountAuthorization OBJECT-TYPE
    SYNTAX      DisplayString
    MAX-ACCESS      read-only
    STATUS      current
    DESCRIPTION
        "The authorization of the account entry."
    ::= { es2310cAccountEntry 2 }

es2310cAccountName  OBJECT-TYPE
    SYNTAX      DisplayString
    MAX-ACCESS      read-write
    STATUS      current
    DESCRIPTION
        "The username of the account entry."
    ::= { es2310cAccountEntry 3 }

es2310cAccountPassword  OBJECT-TYPE
    SYNTAX      DisplayString
    MAX-ACCESS      read-write
    STATUS      current
    DESCRIPTION
        "The password of the account entry. The return value is always '********'."
    ::= { es2310cAccountEntry 4 }

es2310cAccountAddName OBJECT-TYPE
    SYNTAX      DisplayString
    MAX-ACCESS      read-write
    STATUS      current
    DESCRIPTION
        "The account name for adding operation."
    ::= { es2310cAccount 3 }

es2310cAccountAddPassword OBJECT-TYPE
    SYNTAX      DisplayString
    MAX-ACCESS      read-write
    STATUS      current
    DESCRIPTION
        "The account password for adding operation. The return value is always '********'."
    ::= { es2310cAccount 4 }

es2310cDoAccountAdd OBJECT-TYPE
    SYNTAX      INTEGER(0|1)
    MAX-ACCESS      read-write
    STATUS      current
    DESCRIPTION
        "Add account name. OID es2310cAccountAddName and es2310cAccountAddPassword must be
        filled first. Get this oid always return zero.
            1 - add account.
            0 - do nothing."
    ::= { es2310cAccount 5 }

es2310cAccountDel   OBJECT-TYPE
    SYNTAX      INTEGER(2..5)
    MAX-ACCESS      read-write
    STATUS      current
    DESCRIPTION
        "Delete account. The value is valid es2310cAccountIndex(Can't delete administrator)."
    ::= { es2310cAccount 6 }

es2310cSnmp             OBJECT IDENTIFIER ::= { es2310cProduces 2 }

es2310cGetCommunity OBJECT-TYPE
    SYNTAX      DisplayString
    MAX-ACCESS      read-write
    STATUS      current
    DESCRIPTION
        "Get/Set the get-community of the SNMP."
    ::= { es2310cSnmp 1 }

es2310cSetCommunity OBJECT-TYPE
    SYNTAX      DisplayString
    MAX-ACCESS      read-write
    STATUS      current
    DESCRIPTION
        "Get/Set the set-community of the SNMP."
    ::= { es2310cSnmp 2 }

es2310cTrapHostNumber OBJECT-TYPE
    SYNTAX      INTEGER(1..6)
    MAX-ACCESS      read-only
    STATUS      current
    DESCRIPTION
        "Get the number of trap hosts."
    ::= { es2310cSnmp 3 }

es2310cTrapHostTable    OBJECT-TYPE
    SYNTAX      SEQUENCE OF ES2310CTrapHostEntry
    MAX-ACCESS  not-accessible
    STATUS      current
    DESCRIPTION
        "A list of trap host entry. The number of entries are given by the value of es2310cTrapHostNumber."
    ::= { es2310cSnmp 4 }

es2310cTrapHostEntry    OBJECT-TYPE
    SYNTAX      ES2310CTrapHostEntry
    MAX-ACCESS      not-accessible
    STATUS      current
    DESCRIPTION
        "Entry information for trap host."
    INDEX {es2310cTrapHostIndex}
    ::= { es2310cTrapHostTable 1 }

ES2310CTrapHostEntry ::=
SEQUENCE {
    es2310cTrapHostIndex            INTEGER,
    es2310cTrapHostIP           IpAddress,
    es2310cTrapHostPort            INTEGER,
    es2310cTrapHostCommunity       DisplayString
}

es2310cTrapHostIndex    OBJECT-TYPE
    SYNTAX      INTEGER(1..6)
    MAX-ACCESS      read-only
    STATUS      current
    DESCRIPTION
        "The index of the trap host entry."
    ::= { es2310cTrapHostEntry 1 }

es2310cTrapHostIP   OBJECT-TYPE
    SYNTAX      IpAddress
    MAX-ACCESS      read-write
    STATUS      current
    DESCRIPTION
        "The IP of the trap host."
    ::= { es2310cTrapHostEntry 2 }


es2310cTrapHostPort OBJECT-TYPE
    SYNTAX      INTEGER(1..65535)
    MAX-ACCESS      read-write
    STATUS      current
    DESCRIPTION
        "The receiving-port number of the trap host."
    ::= { es2310cTrapHostEntry 3 }


es2310cTrapHostCommunity    OBJECT-TYPE
    SYNTAX      DisplayString
    MAX-ACCESS      read-write
    STATUS      current
    DESCRIPTION
        "The community name for the trap PDU."
    ::= { es2310cTrapHostEntry 4 }

es2310cTrapBootDelayTime OBJECT-TYPE
    SYNTAX      INTEGER(0..120)
    MAX-ACCESS      read-write
    STATUS      current
    DESCRIPTION
        "Get/Set trap boot delay time in second. Default: 0"
    ::= { es2310cSnmp 8 }

es2310cAlarm            OBJECT IDENTIFIER ::= { es2310cProduces 3 }

es2310cEvent            OBJECT IDENTIFIER ::= { es2310cAlarm 1 }

es2310cEventNumber OBJECT-TYPE
    SYNTAX      INTEGER(1..2147483647)
    MAX-ACCESS      read-only
    STATUS      current
    DESCRIPTION
        "Get the total number of alarm events."
    ::= { es2310cEvent 1 }

es2310cEventTable   OBJECT-TYPE
    SYNTAX      SEQUENCE OF ES2310CEventEntry
    MAX-ACCESS  not-accessible
    STATUS      current
    DESCRIPTION
        "A list of alarm event entry. The number of entries are given by the value of es2310cEventNumber."
    ::= { es2310cEvent 2 }

es2310cEventEntry   OBJECT-TYPE
    SYNTAX      ES2310CEventEntry
    MAX-ACCESS      not-accessible
    STATUS      current
    DESCRIPTION
        "Entry information for alarm event."
    INDEX {es2310cEventIndex}
    ::= { es2310cEventTable 1 }

ES2310CEventEntry ::=
SEQUENCE {
    es2310cEventIndex           INTEGER,
    es2310cEventName            DisplayString,
    es2310cEventSendEmail      INTEGER,
    es2310cEventSendTrap       INTEGER
}

es2310cEventIndex   OBJECT-TYPE
    SYNTAX      INTEGER(1..2147483647)
    MAX-ACCESS      read-only
    STATUS      current
    DESCRIPTION
        "The index of the alarm event entry."
    ::= { es2310cEventEntry 1 }

es2310cEventName    OBJECT-TYPE
    SYNTAX      DisplayString
    MAX-ACCESS      read-only
    STATUS      current
    DESCRIPTION
        "The alarm event name."
    ::= { es2310cEventEntry 2 }

es2310cEventSendEmail   OBJECT-TYPE
    SYNTAX      INTEGER(0|1)
    MAX-ACCESS      read-write
    STATUS      current
    DESCRIPTION
        "Send email when alarm event is triggered."
    ::= { es2310cEventEntry 3 }

es2310cEventSendTrap    OBJECT-TYPE
    SYNTAX      INTEGER(0|1)
    MAX-ACCESS      read-write
    STATUS      current
    DESCRIPTION
        "Send trap when alarm event is triggered."
    ::= { es2310cEventEntry 4 }


es2310cEmail            OBJECT IDENTIFIER ::= { es2310cAlarm 2 }

es2310cEmailServer OBJECT-TYPE
    SYNTAX      DisplayString
    MAX-ACCESS      read-write
    STATUS      current
    DESCRIPTION
        "SMTP server for alarm event."
    ::= { es2310cEmail 1 }

es2310cEmailUsername OBJECT-TYPE
    SYNTAX      DisplayString
    MAX-ACCESS      read-write
    STATUS      current
    DESCRIPTION
        "Username of smtp server."
    ::= { es2310cEmail 2 }

es2310cEmailPassword OBJECT-TYPE
    SYNTAX      DisplayString
    MAX-ACCESS      read-write
    STATUS      current
    DESCRIPTION
        "User password of smtp server."
    ::= { es2310cEmail 3 }

es2310cEmailSender OBJECT-TYPE
	SYNTAX      DisplayString
	MAX-ACCESS	    read-write
	STATUS		current
	DESCRIPTION
		"This is the Sender of SMTP server."
	::= {es2310cEmail 4 }

es2310cEmailReturnPath OBJECT-TYPE
	SYNTAX      DisplayString
	MAX-ACCESS	    read-write
	STATUS		current
	DESCRIPTION
		"This is the return path of mail."
	::= { es2310cEmail 5 }

es2310cEmailUserNumber OBJECT-TYPE
    SYNTAX      INTEGER(1..6)
    MAX-ACCESS      read-only
    STATUS      current
    DESCRIPTION
        "The number of the email users that you want to send the alarm notification."
    ::= { es2310cEmail 6 }

es2310cEmailUserTable   OBJECT-TYPE
    SYNTAX      SEQUENCE OF ES2310CEmailUserEntry
    MAX-ACCESS  not-accessible
    STATUS      current
    DESCRIPTION
        "A list of email user entry. The number of entries are given by the value of es2310cEmailUserNumber."
    ::= { es2310cEmail 7 }

es2310cEmailUserEntry   OBJECT-TYPE
    SYNTAX      ES2310CEmailUserEntry
    MAX-ACCESS      not-accessible
    STATUS      current
    DESCRIPTION
        "Entry information for email user entry."
    INDEX {es2310cEmailUserIndex}
    ::= { es2310cEmailUserTable 1 }

ES2310CEmailUserEntry ::=
SEQUENCE {
    es2310cEmailUserIndex           INTEGER,
    es2310cEmailUserAddress         DisplayString
}

es2310cEmailUserIndex   OBJECT-TYPE
    SYNTAX      INTEGER(1..6)
    MAX-ACCESS      read-only
    STATUS      current
    DESCRIPTION
        "The index of the email user entry."
    ::= { es2310cEmailUserEntry 1 }

es2310cEmailUserAddress OBJECT-TYPE
    SYNTAX      DisplayString
    MAX-ACCESS      read-write
    STATUS      current
    DESCRIPTION
        "The email address of the email user entry."
    ::= { es2310cEmailUserEntry 2 }

es2310cTftp             OBJECT IDENTIFIER ::= { es2310cProduces 4 }

es2310cTftpServer OBJECT-TYPE
    SYNTAX      IpAddress
    MAX-ACCESS      read-write
    STATUS      current
    DESCRIPTION
        "Get/Set the tftp server."
    ::= { es2310cTftp 1 }

es2310cConfiguration            OBJECT IDENTIFIER ::= { es2310cProduces 5 }

es2310cSaveRestore              OBJECT IDENTIFIER ::= { es2310cConfiguration 1 }

es2310cSaveStart OBJECT-TYPE
    SYNTAX      INTEGER(0|1)
    MAX-ACCESS      read-write
    STATUS      current
    DESCRIPTION
        "Save current configuration into flash memory (start section).
        Get this oid always return zero.
            1 - save.
            0 - do nothing. "
    ::= { es2310cSaveRestore 1 }

es2310cSaveUser OBJECT-TYPE
    SYNTAX      INTEGER(0|1)
    MAX-ACCESS      read-write
    STATUS      current
    DESCRIPTION
        "Save current configuration into flash memory (user config section).
        Get this oid always return zero.
            1 - save.
            0 - do nothing. "
    ::= { es2310cSaveRestore 2 }

es2310cRestoreDefault OBJECT-TYPE
    SYNTAX      INTEGER(0|1|2)
    MAX-ACCESS      read-write
    STATUS      current
    DESCRIPTION
        "Restore factory default configuration.
        Get this oid always return zero.
            2 - restore default included default ip address.
        1 - restore default without changing current ip address.
            0 - do nothing. "
    ::= { es2310cSaveRestore 3 }

es2310cRestoreUser OBJECT-TYPE
    SYNTAX      INTEGER(0|1)
    MAX-ACCESS      read-write
    STATUS      current
    DESCRIPTION
        "Restore user configuration.
        Get this oid always return zero.
            1 - restore.
            0 - do nothing. "
    ::= { es2310cSaveRestore 4 }


es2310cConfigFile               OBJECT IDENTIFIER ::= { es2310cConfiguration 2 }

es2310cExportConfigName OBJECT-TYPE
    SYNTAX      DisplayString
    MAX-ACCESS      read-write
    STATUS      current
    DESCRIPTION
        "Get/Set export config file path and name."
    ::= { es2310cConfigFile 1 }

es2310cDoExportConfig OBJECT-TYPE
    SYNTAX      INTEGER(1|2)
    MAX-ACCESS      read-write
    STATUS      current
    DESCRIPTION
        "Do export-config.
        Get this oid always return zero.
            1   -   export start section.
            2   -   export user-conf section."
    ::= { es2310cConfigFile 2 }

es2310cImportConfigName OBJECT-TYPE
    SYNTAX      DisplayString
    MAX-ACCESS      read-write
    STATUS      current
    DESCRIPTION
        "Get/Set export config file path and name."
    ::= { es2310cConfigFile 3 }

es2310cDoImportConfig OBJECT-TYPE
    SYNTAX      INTEGER(1|2)
    MAX-ACCESS      read-write
    STATUS      current
    DESCRIPTION
        "Do import-config.
        Get this oid always return zero.
            1   -   import start section.
            2   -   import user-conf section."
    ::= { es2310cConfigFile 4 }

es2310cDiagnostic               OBJECT IDENTIFIER ::= { es2310cProduces 6 }

es2310cEEPROMTest OBJECT-TYPE
    SYNTAX      DisplayString
    MAX-ACCESS      read-only
    STATUS      current
    DESCRIPTION
        "EEPROM access test."
    ::= { es2310cDiagnostic 1 }

es2310cUartTest OBJECT-TYPE
    SYNTAX      DisplayString
    MAX-ACCESS      read-only
    STATUS      current
    DESCRIPTION
        "UART access test."
    ::= { es2310cDiagnostic 2 }

es2310cDramTest OBJECT-TYPE
    SYNTAX      DisplayString
    MAX-ACCESS      read-only
    STATUS      current
    DESCRIPTION
        "DRAM access test."
    ::= { es2310cDiagnostic 3 }

es2310cFlashTest OBJECT-TYPE
    SYNTAX      DisplayString
    MAX-ACCESS      read-only
    STATUS      current
    DESCRIPTION
        "Flash memory access test."
    ::= { es2310cDiagnostic 4 }

es2310cInternalLoopbackTest OBJECT-TYPE
    SYNTAX      DisplayString
    MAX-ACCESS      read-only
    STATUS      current
    DESCRIPTION
        "Internal loopback test."
    ::= { es2310cDiagnostic 5 }

es2310cExternalLoopbackTest OBJECT-TYPE
    SYNTAX      DisplayString
    MAX-ACCESS      read-only
    STATUS      current
    DESCRIPTION
        "External loopback test."
    ::= { es2310cDiagnostic 6 }

es2310cPingTest OBJECT-TYPE
    SYNTAX      DisplayString
    MAX-ACCESS      read-write
    STATUS      current
    DESCRIPTION
        "Set the host address that you want to ping and the system will return the test result."
    ::= { es2310cDiagnostic 7 }


es2310cLog              OBJECT IDENTIFIER ::= { es2310cProduces 7 }

es2310cClearLog OBJECT-TYPE
    SYNTAX      INTEGER(0|1)
    MAX-ACCESS      read-write
    STATUS      current
    DESCRIPTION
        "Clear system log.
        Get this oid always return zero.
            1 - clear log.
            0 - do nothing. "
    ::= { es2310cLog 1 }

es2310cUploadLog OBJECT-TYPE
    SYNTAX      INTEGER(0|1)
    MAX-ACCESS      read-write
    STATUS      current
    DESCRIPTION
        "Upload current system log. Set the correct tftp server first.
        The format of log file is 'ModelName_SerialNumbuer_YYMMDD_HHMM'.
        Get this oid always return zero.
            1 - upload log
            0 - do nothing. "
    ::= { es2310cLog 2 }

es2310cAutoUploadLogState OBJECT-TYPE
    SYNTAX      INTEGER(0|1)
    MAX-ACCESS      read-write
    STATUS      current
    DESCRIPTION
        "Enable log auto-upload function. Set the correct tftp server first.
        The format of log file is 'ModelName_SerialNumbuer_YYMMDD_HHMM'.
        Get this oid always return zero.
            1 - Enable auto-upload
            0 - do nothing. "
    ::= { es2310cLog 3 }

es2310cLogNumber OBJECT-TYPE
    SYNTAX      INTEGER(0..120)
    MAX-ACCESS      read-only
    STATUS      current
    DESCRIPTION
        "Get the number of current system log. "
    ::= { es2310cLog 4 }

es2310cLogTable OBJECT-TYPE
    SYNTAX      SEQUENCE OF ES2310CLogEntry
    MAX-ACCESS  not-accessible
    STATUS      current
    DESCRIPTION
        "A list of log entry. The number of entries are given by the value of es2310cLogNumber."
    ::= { es2310cLog 5 }

es2310cLogEntry OBJECT-TYPE
    SYNTAX      ES2310CLogEntry
    MAX-ACCESS      not-accessible
    STATUS      current
    DESCRIPTION
        "Entry information for system log."
    INDEX {es2310cLogIndex}
    ::= { es2310cLogTable 1 }

ES2310CLogEntry ::=
SEQUENCE {
    es2310cLogIndex         INTEGER,
    es2310cLogEvent             DisplayString
}

es2310cLogIndex OBJECT-TYPE
    SYNTAX      INTEGER(1..120)
    MAX-ACCESS      read-only
    STATUS      current
    DESCRIPTION
        "The index of the log entry."
    ::= { es2310cLogEntry 1 }

es2310cLogEvent OBJECT-TYPE
    SYNTAX      DisplayString
    MAX-ACCESS      read-only
    STATUS      current
    DESCRIPTION
        "The detail information of the log entry."
    ::= { es2310cLogEntry 2 }

es2310cFirmware             OBJECT IDENTIFIER ::= { es2310cProduces 8 }

es2310cFirmwareFileName OBJECT-TYPE
    SYNTAX      DisplayString
    MAX-ACCESS      read-write
    STATUS      current
    DESCRIPTION
        "Get/Set the path and filename for firmware upgrading."
    ::= { es2310cFirmware 1 }

es2310cDoFirmwareUpgrade OBJECT-TYPE
    SYNTAX      INTEGER(0|1)
    MAX-ACCESS      read-write
    STATUS      current
    DESCRIPTION
        "Do firmware upgrade. Get this oid always return zero.
            1 - do firmware upgrade.
            0 - do nothing."
    ::= { es2310cFirmware 2 }

es2310cPort             OBJECT IDENTIFIER ::= { es2310cProduces 9 }

es2310cPortStatus               OBJECT IDENTIFIER ::= { es2310cPort 1 }

es2310cPortStatusNumber OBJECT-TYPE
    SYNTAX      INTEGER(1..2147483647)
    MAX-ACCESS      read-only
    STATUS      current
    DESCRIPTION
        "Get the number of port state."
    ::= { es2310cPortStatus 1 }

es2310cPortStatusTable  OBJECT-TYPE
    SYNTAX      SEQUENCE OF ES2310CPortStatusEntry
    MAX-ACCESS  not-accessible
    STATUS      current
    DESCRIPTION
        "A list of port status entry. The number of entries are given by the value of es2310cPortStatusNumber."
    ::= { es2310cPortStatus 2 }

es2310cPortStatusEntry  OBJECT-TYPE
    SYNTAX      ES2310CPortStatusEntry
    MAX-ACCESS      not-accessible
    STATUS      current
    DESCRIPTION
        "Entry(s) for port status information."
    INDEX {es2310cPortStatusIndex}
    ::= { es2310cPortStatusTable 1 }

ES2310CPortStatusEntry ::=
SEQUENCE {
    es2310cPortStatusIndex          INTEGER,
    es2310cPortStatusMedia          DisplayString,
    es2310cPortStatusLink           DisplayString,
    es2310cPortStatusPortState      DisplayString,
    es2310cPortStatusAutoNego       DisplayString,
    es2310cPortStatusSpdDpx         DisplayString,
    es2310cPortStatusRxPause        DisplayString,
    es2310cPortStatusTxPause        DisplayString,
    es2310cPortStatusDescription     DisplayString
}

es2310cPortStatusIndex  OBJECT-TYPE
    SYNTAX      INTEGER(1..2147483647)
    MAX-ACCESS      read-only
    STATUS      current
    DESCRIPTION
        "The index of the port status entry."
    ::= { es2310cPortStatusEntry 1 }

es2310cPortStatusMedia  OBJECT-TYPE
    SYNTAX      DisplayString
    MAX-ACCESS      read-only
    STATUS      current
    DESCRIPTION
        "The port media type of the port status entry."
    ::= { es2310cPortStatusEntry 2 }

es2310cPortStatusLink   OBJECT-TYPE
    SYNTAX      DisplayString
    MAX-ACCESS      read-only
    STATUS      current
    DESCRIPTION
        "The port link of the port status entry."
    ::= { es2310cPortStatusEntry 3 }

es2310cPortStatusPortState  OBJECT-TYPE
    SYNTAX      DisplayString
    MAX-ACCESS      read-only
    STATUS      current
    DESCRIPTION
        "The port state of the port status entry."
    ::= { es2310cPortStatusEntry 4 }

es2310cPortStatusAutoNego   OBJECT-TYPE
    SYNTAX      DisplayString
    MAX-ACCESS      read-only
    STATUS      current
    DESCRIPTION
        "The auto negotiation of the port status entry."
    ::= { es2310cPortStatusEntry 5 }

es2310cPortStatusSpdDpx     OBJECT-TYPE
    SYNTAX      DisplayString
    MAX-ACCESS      read-only
    STATUS      current
    DESCRIPTION
        "The speed/duplex of the port status entry."
    ::= { es2310cPortStatusEntry 6 }

es2310cPortStatusRxPause    OBJECT-TYPE
    SYNTAX      DisplayString
    MAX-ACCESS      read-only
    STATUS      current
    DESCRIPTION
        "The Rx Pause of the port status entry."
    ::= { es2310cPortStatusEntry 7 }

es2310cPortStatusTxPause    OBJECT-TYPE
    SYNTAX      DisplayString
    MAX-ACCESS      read-only
    STATUS      current
    DESCRIPTION
        "The Tx Pause of the port status entry."
    ::= { es2310cPortStatusEntry 8 }

es2310cPortStatusDescription    OBJECT-TYPE
    SYNTAX      DisplayString
    MAX-ACCESS  read-only
    STATUS      current
    DESCRIPTION
        "The description of port."
    ::= { es2310cPortStatusEntry 9 }

es2310cPortConf             OBJECT IDENTIFIER ::= { es2310cPort 2 }

es2310cPortConfNumber OBJECT-TYPE
    SYNTAX      INTEGER(1..2147483647)
    MAX-ACCESS      read-only
    STATUS      current
    DESCRIPTION
        "Get the number of port configuration."
    ::= { es2310cPortConf 1 }

es2310cPortConfTable    OBJECT-TYPE
    SYNTAX      SEQUENCE OF ES2310CPortConfEntry
    MAX-ACCESS  not-accessible
    STATUS      current
    DESCRIPTION
        "A list of port configuration entry. The number of entries are given by the value of es2310cPortConfNumber."
    ::= { es2310cPortConf 2 }

es2310cPortConfEntry    OBJECT-TYPE
    SYNTAX      ES2310CPortConfEntry
    MAX-ACCESS      not-accessible
    STATUS      current
    DESCRIPTION
        "Entry(s) for port configuration information."
    INDEX {es2310cPortConfIndex}
    ::= { es2310cPortConfTable 1 }

ES2310CPortConfEntry ::=
SEQUENCE {
    es2310cPortConfIndex            INTEGER,
    es2310cPortConfPortState        INTEGER,
    es2310cPortConfSpdDpx           INTEGER,
    es2310cPortConfFlwCtrl          INTEGER,
    es2310cPortConfDescription      DisplayString
}

es2310cPortConfIndex    OBJECT-TYPE
    SYNTAX      INTEGER(1..2147483647)
    MAX-ACCESS      read-only
    STATUS      current
    DESCRIPTION
        "The index of the port configuration entry."
    ::= { es2310cPortConfEntry 1 }

es2310cPortConfPortState    OBJECT-TYPE
    SYNTAX      INTEGER(0|1)
    MAX-ACCESS      read-write
    STATUS      current
    DESCRIPTION
        "The port state of the port configuration entry.
         0 - disabled.
         1 - enabled. "
    ::= { es2310cPortConfEntry 2 }

es2310cPortConfSpdDpx   OBJECT-TYPE
    SYNTAX      INTEGER(0..5)
    MAX-ACCESS      read-write
    STATUS      current
    DESCRIPTION
        "The speed/duplex of the port configuration entry.
         0 - auto.
         1 - 10M/Half.
         2 - 10M/Full.
         3 - 100M/Half.
         4 - 100M/Full.
         5 - 1G/Full.  "
    ::= { es2310cPortConfEntry 3 }

es2310cPortConfFlwCtrl  OBJECT-TYPE
    SYNTAX      INTEGER(0|1)
    MAX-ACCESS      read-write
    STATUS      current
    DESCRIPTION
        "The flow control of the port configuration entry.
         0 - asymmetric.
         1 - symmetric.  "
    ::= { es2310cPortConfEntry 4 }

es2310cPortConfDescription  OBJECT-TYPE
    SYNTAX      DisplayString
    MAX-ACCESS  read-write
    STATUS      current
    DESCRIPTION
        "The description of port."
    ::= { es2310cPortConfEntry 5 }

es2310cPortBandwidth            OBJECT IDENTIFIER ::= { es2310cPort 3 }

es2310cPortBandwidthTable   OBJECT-TYPE
    SYNTAX      SEQUENCE OF ES2310CPortBandwidthEntry
    MAX-ACCESS  not-accessible
    STATUS      current
    DESCRIPTION
        "This is a list of port bandwidth entry."
    ::= { es2310cPortBandwidth 1 }

ES2310CPortBandwidthEntry ::=
SEQUENCE {
    es2310cPortBandwidthIndex                 INTEGER,
    es2310cPortBandwidthIngressRate        INTEGER,
    es2310cPortBandwidthEgressRate         INTEGER
}

es2310cPortBandwidthEntry   OBJECT-TYPE
    SYNTAX      ES2310CPortBandwidthEntry
    MAX-ACCESS      not-accessible
    STATUS      current
    DESCRIPTION
        "This is the Entry(s) for port bandwidth configuration."
    INDEX {es2310cPortBandwidthIndex}
    ::= { es2310cPortBandwidthTable 1 }

es2310cPortBandwidthIndex   OBJECT-TYPE
    SYNTAX      INTEGER(1..10)
    MAX-ACCESS      read-only
    STATUS      current
    DESCRIPTION
        "This is the index of the port bandwidth entry."
    ::= { es2310cPortBandwidthEntry 1 }

es2310cPortBandwidthIngressRate OBJECT-TYPE
    SYNTAX      INTEGER(66..1024000)
    MAX-ACCESS      read-write
    STATUS      current
    DESCRIPTION
        "Get/Set the port bandwidth ingress rate.
         Fast Ethernet port range: 66~102400(Kb)
         Gigabit Ethernet port range: 66~1024000(Kb)"
    ::= { es2310cPortBandwidthEntry 2 }

es2310cPortBandwidthEgressRate  OBJECT-TYPE
    SYNTAX      INTEGER(66..1024000)
    MAX-ACCESS      read-write
    STATUS      current
    DESCRIPTION
        "Get/Set the port bandwidth egress rate.
         Fast Ethernet port range: 66~102400(Kb)
         Gigabit Ethernet port range: 66~1024000(Kb)"
    ::= { es2310cPortBandwidthEntry 3 }

es2310cPortBandwidthStormType   OBJECT-TYPE
    SYNTAX      INTEGER(0..4)
    MAX-ACCESS      read-write
    STATUS      current
    DESCRIPTION
        "This is the bandwidth storm type.
        0:Disable
                1:Broadcast Storm Control
                2:Multicast Storm Control
                3:Unknown Unicast Storm Control
                4:Broadcast, Multicast, and Unknown Unicast Storm Control"
    ::= { es2310cPortBandwidth 2 }

es2310cPortBandwidthStormRate   OBJECT-TYPE
    SYNTAX      INTEGER(1..100)
    MAX-ACCESS      read-write
    STATUS      current
    DESCRIPTION
        "This is the storm rate."
    ::= { es2310cPortBandwidth 3 }

es2310cPortSFPInfo               OBJECT IDENTIFIER ::= { es2310cPort 4 }

es2310cPortSFPInfoNumber OBJECT-TYPE
    SYNTAX      INTEGER(1..2147483647)
    MAX-ACCESS      read-only
    STATUS      current
    DESCRIPTION
        "Get the number of sfp info entry."
    ::= { es2310cPortSFPInfo 1 }

es2310cPortSFPInfoTable  OBJECT-TYPE
    SYNTAX      SEQUENCE OF ES2310CPORTSFPInfoEntry
    MAX-ACCESS  not-accessible
    STATUS      current
    DESCRIPTION
        "A list of sfp info entry. The numbers of entries are given by the value of es2310cPortSFPInfoNumber."
    ::= { es2310cPortSFPInfo 2 }

ES2310CPORTSFPInfoEntry ::=
SEQUENCE {
    es2310cPortSFPInfoIndex      INTEGER,
    es2310cPortSFPConnectorType  DisplayString,
    es2310cPortSFPFiberType      DisplayString,
    es2310cPortSFPWavelength     DisplayString,
    es2310cPortSFPBaudRate       DisplayString,
    es2310cPortSFPVendorOUI      DisplayString,
    es2310cPortSFPVendorName     DisplayString,
    es2310cPortSFPVendorPN       DisplayString,
    es2310cPortSFPVendorRev      DisplayString,
    es2310cPortSFPVendorSN       DisplayString,
    es2310cPortSFPDateCode       DisplayString,
    es2310cPortSFPTemperature    DisplayString,
    es2310cPortSFPVcc            DisplayString,
    es2310cPortSFPTxBias         DisplayString,
    es2310cPortSFPTxPWR          DisplayString,
    es2310cPortSFPRxPWR          DisplayString
}

es2310cPortSFPInfoEntry  OBJECT-TYPE
    SYNTAX      ES2310CPORTSFPInfoEntry
    MAX-ACCESS      not-accessible
    STATUS      current
    DESCRIPTION
        "Entry(s) for SFP information."
    INDEX {es2310cPortSFPInfoIndex}
    ::= { es2310cPortSFPInfoTable 1 }

es2310cPortSFPInfoIndex  OBJECT-TYPE
    SYNTAX      INTEGER(1..2147483647)
    MAX-ACCESS      read-only
    STATUS      current
    DESCRIPTION
        "The index of the sfp info entry."
    ::= { es2310cPortSFPInfoEntry 1 }

es2310cPortSFPConnectorType  OBJECT-TYPE
    SYNTAX      DisplayString
    MAX-ACCESS      read-only
    STATUS      current
    DESCRIPTION
        "Get connector type of the sfp."
    ::= { es2310cPortSFPInfoEntry 2 }

es2310cPortSFPFiberType  OBJECT-TYPE
    SYNTAX      DisplayString
    MAX-ACCESS      read-only
    STATUS      current
    DESCRIPTION
        "Get fiber type of the sfp."
    ::= { es2310cPortSFPInfoEntry 3 }

es2310cPortSFPWavelength OBJECT-TYPE
    SYNTAX      DisplayString
    MAX-ACCESS      read-only
    STATUS      current
    DESCRIPTION
        "Get tx central wavelength of the sfp."
    ::= { es2310cPortSFPInfoEntry 4 }

es2310cPortSFPBaudRate   OBJECT-TYPE
    SYNTAX      DisplayString
    MAX-ACCESS      read-only
    STATUS      current
    DESCRIPTION
        "Get baud rate of the sfp."
    ::= { es2310cPortSFPInfoEntry 5 }

es2310cPortSFPVendorOUI  OBJECT-TYPE
    SYNTAX      DisplayString
    MAX-ACCESS      read-only
    STATUS      current
    DESCRIPTION
        "Get vendor OUI of the sfp."
    ::= { es2310cPortSFPInfoEntry 6 }

es2310cPortSFPVendorName OBJECT-TYPE
    SYNTAX      DisplayString
    MAX-ACCESS      read-only
    STATUS      current
    DESCRIPTION
        "Get vendor name of the sfp."
    ::= { es2310cPortSFPInfoEntry 7 }

es2310cPortSFPVendorPN   OBJECT-TYPE
    SYNTAX      DisplayString
    MAX-ACCESS      read-only
    STATUS      current
    DESCRIPTION
        "Get vendor part number of the sfp."
    ::= { es2310cPortSFPInfoEntry 8 }

es2310cPortSFPVendorRev  OBJECT-TYPE
    SYNTAX      DisplayString
    MAX-ACCESS      read-only
    STATUS      current
    DESCRIPTION
        "Get vendor revision number of the sfp."
    ::= { es2310cPortSFPInfoEntry 9 }

es2310cPortSFPVendorSN   OBJECT-TYPE
    SYNTAX      DisplayString
    MAX-ACCESS      read-only
    STATUS      current
    DESCRIPTION
        "Get vendor serial number of the sfp."
    ::= { es2310cPortSFPInfoEntry 10 }

es2310cPortSFPDateCode   OBJECT-TYPE
    SYNTAX      DisplayString
    MAX-ACCESS      read-only
    STATUS      current
    DESCRIPTION
        "Get data code of the sfp."
    ::= { es2310cPortSFPInfoEntry 11 }

es2310cPortSFPTemperature    OBJECT-TYPE
    SYNTAX      DisplayString
    MAX-ACCESS      read-only
    STATUS      current
    DESCRIPTION
        "Get current temperature of the sfp."
    ::= { es2310cPortSFPInfoEntry 12 }

es2310cPortSFPVcc    OBJECT-TYPE
    SYNTAX      DisplayString
    MAX-ACCESS      read-only
    STATUS      current
    DESCRIPTION
        "Get current internal supply voltage of the sfp."
    ::= { es2310cPortSFPInfoEntry 13 }

es2310cPortSFPTxBias OBJECT-TYPE
    SYNTAX      DisplayString
    MAX-ACCESS      read-only
    STATUS      current
    DESCRIPTION
        "Get current TX Bias of the sfp."
    ::= { es2310cPortSFPInfoEntry 14 }

es2310cPortSFPTxPWR  OBJECT-TYPE
    SYNTAX      DisplayString
    MAX-ACCESS      read-only
    STATUS      current
    DESCRIPTION
        "Get current TX output power of the sfp."
    ::= { es2310cPortSFPInfoEntry 15 }

es2310cPortSFPRxPWR  OBJECT-TYPE
    SYNTAX      DisplayString
    MAX-ACCESS      read-only
    STATUS      current
    DESCRIPTION
        "Get current Received Power of the sfp."
    ::= { es2310cPortSFPInfoEntry 16 }

es2310cLoopDetectedConf             OBJECT IDENTIFIER ::= { es2310cProduces 10 }

es2310cLoopDetectedNumber OBJECT-TYPE
    SYNTAX      INTEGER(1..2147483647)
    MAX-ACCESS      read-only
    STATUS      current
    DESCRIPTION
        "Get the number of loop detected entry."
    ::= { es2310cLoopDetectedConf 1 }

es2310cLoopDetectedTable    OBJECT-TYPE
    SYNTAX      SEQUENCE OF ES2310CLoopDetectedEntry
    MAX-ACCESS  not-accessible
    STATUS      current
    DESCRIPTION
        "A list of loop detected entry. The number of entries are given by the value of es2310cLoopDetectedNumber."
    ::= { es2310cLoopDetectedConf 2 }

es2310cLoopDetectedEntry    OBJECT-TYPE
    SYNTAX      ES2310CLoopDetectedEntry
    MAX-ACCESS      not-accessible
    STATUS      current
    DESCRIPTION
        "Entry(s) for loop detected information."
    INDEX {es2310cLoopDetectedfIndex}
    ::= { es2310cLoopDetectedTable 1 }

ES2310CLoopDetectedEntry ::=
SEQUENCE {
    es2310cLoopDetectedfIndex           INTEGER,
    es2310cLoopDetectedStateEbl         INTEGER,
    es2310cLoopDetectedCurrentStatus    INTEGER,
    es2310cLoopDetectedResumed          INTEGER
}

es2310cLoopDetectedfIndex   OBJECT-TYPE
    SYNTAX      INTEGER(1..2147483647)
    MAX-ACCESS      read-only
    STATUS      current
    DESCRIPTION
        "The index of the loop detected entry."
    ::= { es2310cLoopDetectedEntry 1 }

es2310cLoopDetectedStateEbl OBJECT-TYPE
    SYNTAX      INTEGER(0|1)
    MAX-ACCESS      read-write
    STATUS      current
    DESCRIPTION
        "The state of the loop detected entry.
         0 - disabled.
         1 - enabled. "
    ::= { es2310cLoopDetectedEntry 2 }

es2310cLoopDetectedCurrentStatus    OBJECT-TYPE
    SYNTAX      INTEGER(0|1)
    MAX-ACCESS      read-only
    STATUS      current
    DESCRIPTION
        "The current status of the loop detected port.
         0 - unlocked
         1 - locked due to the loop condition "
    ::= { es2310cLoopDetectedEntry 3 }

es2310cLoopDetectedResumed  OBJECT-TYPE
    SYNTAX      INTEGER(0|1)
    MAX-ACCESS      read-write
    STATUS      current
    DESCRIPTION
        "unlock the port which is locked due to loop condition. Get this oid always return zero.
         1 - unlock the port,
         0 - do nothing"
    ::= { es2310cLoopDetectedEntry 4 }

es2310cLoopDetectedAction OBJECT-TYPE
    SYNTAX      INTEGER(0|1)
    MAX-ACCESS      read-write
    STATUS      current
    DESCRIPTION
        "Set the corresponding action while loop is detected.
         1 - locked the loop port,
         0 - do nothing."
    ::= { es2310cLoopDetectedConf 3 }

es2310cMacTableInfo             OBJECT IDENTIFIER ::= { es2310cProduces 11 }

es2310cMacTableMaintenance       OBJECT IDENTIFIER ::= { es2310cMacTableInfo 1 }

es2310cMacTableAgingTime  OBJECT-TYPE
    SYNTAX      INTEGER(0|10..1000000)
    MAX-ACCESS  read-write
    STATUS      current
    DESCRIPTION
        "Set the Mac Table Aging Time (10~1000000 Secs).
         0 : Disable.
        "
    ::= { es2310cMacTableMaintenance 1 }

es2310cMacTableFlush  OBJECT-TYPE
    SYNTAX      INTEGER(0|1)
    MAX-ACCESS  read-write
    STATUS      current
    DESCRIPTION
        "1 : Flush Mac Table."
    ::= { es2310cMacTableMaintenance 2 }

es2310cMacTableLearnPortLimitTable  OBJECT-TYPE
    SYNTAX      SEQUENCE OF ES2310CMacTableLearnPortLimitEntry
    MAX-ACCESS  not-accessible
    STATUS      current
    DESCRIPTION
        "This is a list of MAC Learning Limitentry."
    ::= { es2310cMacTableMaintenance 3 }

ES2310CMacTableLearnPortLimitEntry ::=
SEQUENCE {
    es2310cMacTableLearnPortLimitIndex   INTEGER,
    es2310cMacTableLearnPortLimit           INTEGER
}

es2310cMacTableLearnPortLimitEntry  OBJECT-TYPE
    SYNTAX      ES2310CMacTableLearnPortLimitEntry
    MAX-ACCESS  not-accessible
    STATUS      current
    DESCRIPTION
        "Entry(s) for Mac Table Port Learning Limit."
    INDEX {es2310cMacTableLearnPortLimitIndex}
    ::= { es2310cMacTableLearnPortLimitTable 1 }

es2310cMacTableLearnPortLimitIndex  OBJECT-TYPE
    SYNTAX      INTEGER(1..10)
    MAX-ACCESS  not-accessible
    STATUS      current
    DESCRIPTION
        "The index of the Mac Table Learning Limit entry."
    ::= { es2310cMacTableLearnPortLimitEntry 1 }

es2310cMacTableLearnPortLimit  OBJECT-TYPE
    SYNTAX      INTEGER(0..8191)
    MAX-ACCESS  read-write
    STATUS      current
    DESCRIPTION
        "Port Learning Limit (0~8191)."
    ::= { es2310cMacTableLearnPortLimitEntry 2 }

es2310cMacTableStaticMac       OBJECT IDENTIFIER ::= { es2310cMacTableInfo 3 }

es2310cMacTableStaticMacNumber  OBJECT-TYPE
    SYNTAX      INTEGER(0..1024)
    MAX-ACCESS  read-only
    STATUS      current
    DESCRIPTION
        "This is number of static Mac table entry"
    ::= { es2310cMacTableStaticMac 1 }

es2310cMacTableStaticMacEntryCreate  OBJECT-TYPE
    SYNTAX      INTEGER(0..1024)
    MAX-ACCESS  read-write
    STATUS      current
    DESCRIPTION
        "Creat a static mac entry.
         Set 1: add a new entry,
         Get: the number means index."
    ::= { es2310cMacTableStaticMac 2 }

es2310cMacTableStaticMacTable  OBJECT-TYPE
    SYNTAX      SEQUENCE OF ES2310CMacTableStaticMacEntry
    MAX-ACCESS  not-accessible
    STATUS      current
    DESCRIPTION
        "This is a list of static MAC table."
    ::= { es2310cMacTableStaticMac 3 }

ES2310CMacTableStaticMacEntry ::=
SEQUENCE {
    es2310cMacTableStaticMacIndex        INTEGER,
    es2310cMacTableStaticMacAddress      DisplayString,
    es2310cMacTableStaticMacVid           INTEGER,
    es2310cMacTableStaticMacQueue           INTEGER,
    es2310cMacTableStaticMacFwRule          INTEGER,
    es2310cMacTableStaticMacPort        INTEGER,
    es2310cMacTableStaticMacEntryAction     INTEGER
}

es2310cMacTableStaticMacEntry  OBJECT-TYPE
    SYNTAX      ES2310CMacTableStaticMacEntry
    MAX-ACCESS  not-accessible
    STATUS      current
    DESCRIPTION
        "Entry(s) for Static Mac Table."
    INDEX {es2310cMacTableStaticMacIndex}
    ::= { es2310cMacTableStaticMacTable 1 }

es2310cMacTableStaticMacIndex  OBJECT-TYPE
    SYNTAX      INTEGER(1..1024)
    MAX-ACCESS      not-accessible
    STATUS      current
    DESCRIPTION
        "The index of the static Mac Table."
    ::= { es2310cMacTableStaticMacEntry 1 }

es2310cMacTableStaticMacAddress  OBJECT-TYPE
    SYNTAX      DisplayString
    MAX-ACCESS  read-write
    STATUS      current
    DESCRIPTION
        "The mac address of the static mac table entry."
    ::= { es2310cMacTableStaticMacEntry 2 }

es2310cMacTableStaticMacVid  OBJECT-TYPE
    SYNTAX      INTEGER(1..4094)
    MAX-ACCESS  read-write
    STATUS      current
    DESCRIPTION
        "The vlan id of the static mac table entry."
    ::= { es2310cMacTableStaticMacEntry 3 }

es2310cMacTableStaticMacQueue  OBJECT-TYPE
    SYNTAX      INTEGER(0..3)
    MAX-ACCESS  read-write
    STATUS      current
    DESCRIPTION
        "The queue of the static mac table entry."
    ::= { es2310cMacTableStaticMacEntry 4 }

es2310cMacTableStaticMacFwRule  OBJECT-TYPE
    SYNTAX      INTEGER(0..2)
    MAX-ACCESS  read-write
    STATUS      current
    DESCRIPTION
        "The forwarding rule of the static mac table entry.
         0 : static
         1 : Static with Destination Drop
         2 : Static with Source Drop
        "
    ::= { es2310cMacTableStaticMacEntry 5 }

es2310cMacTableStaticMacPort  OBJECT-TYPE
    SYNTAX      INTEGER(1..10)
    MAX-ACCESS  read-write
    STATUS      current
    DESCRIPTION
        "The port of the static mac table entry."
    ::= { es2310cMacTableStaticMacEntry 6 }

es2310cMacTableStaticMacEntryAction  OBJECT-TYPE
    SYNTAX      INTEGER(1..3)
    MAX-ACCESS  read-write
    STATUS      current
    DESCRIPTION
        "The action of the static mac table entry.
         1:action
         2:non-action
         3:delete"
    ::= { es2310cMacTableStaticMacEntry 7 }

es2310cMacTableMacAlias       OBJECT IDENTIFIER ::= { es2310cMacTableInfo 4 }

es2310cMacTableMacAliasNumber  OBJECT-TYPE
    SYNTAX      INTEGER(0..8192)
    MAX-ACCESS  read-only
    STATUS      current
    DESCRIPTION
        "This is number of static Mac table entry"
    ::= { es2310cMacTableMacAlias 1 }

es2310cMacTableMacAliasEntryCreate  OBJECT-TYPE
    SYNTAX      INTEGER(0..8192)
    MAX-ACCESS  read-write
    STATUS      current
    DESCRIPTION
        "Creat a static mac alias entry.
         Set 1: add a new entry,
         Get: the number means index."
    ::= { es2310cMacTableMacAlias 2 }

es2310cMacTableMacAliasTable  OBJECT-TYPE
    SYNTAX      SEQUENCE OF ES2310CMacTableMacAliasEntry
    MAX-ACCESS  not-accessible
    STATUS      current
    DESCRIPTION
        "This is a list of MAC Alias table."
    ::= { es2310cMacTableMacAlias 3 }

ES2310CMacTableMacAliasEntry ::=
SEQUENCE {
    es2310cMacTableMacAliasIndex        INTEGER,
    es2310cMacTableMacAliasAddress      DisplayString,
    es2310cMacTableMacAliasAlias        DisplayString,
    es2310cMacTableMacAliasEntryAction  INTEGER
}

es2310cMacTableMacAliasEntry  OBJECT-TYPE
    SYNTAX      ES2310CMacTableMacAliasEntry
    MAX-ACCESS  not-accessible
    STATUS      current
    DESCRIPTION
        "Entry(s) for Alias Mac Table."
    INDEX {es2310cMacTableMacAliasIndex}
    ::= { es2310cMacTableMacAliasTable 1 }

es2310cMacTableMacAliasIndex  OBJECT-TYPE
    SYNTAX      INTEGER(1..1024)
    MAX-ACCESS      not-accessible
    STATUS      current
    DESCRIPTION
        "The index of the Alias Mac Table."
    ::= { es2310cMacTableMacAliasEntry 1 }

es2310cMacTableMacAliasAddress  OBJECT-TYPE
    SYNTAX      DisplayString
    MAX-ACCESS      read-write
    STATUS      current
    DESCRIPTION
        "The Mac address of the Alias Mac Table."
    ::= { es2310cMacTableMacAliasEntry 2 }

es2310cMacTableMacAliasAlias  OBJECT-TYPE
    SYNTAX      DisplayString
    MAX-ACCESS      read-write
    STATUS      current
    DESCRIPTION
        "The Mac Alias of the Alias Mac Table."
    ::= { es2310cMacTableMacAliasEntry 3 }

es2310cMacTableMacAliasEntryAction  OBJECT-TYPE
    SYNTAX      INTEGER(1..3)
    MAX-ACCESS  read-write
    STATUS      current
    DESCRIPTION
        "The action of the alias mac table entry.
         1:action
         2:non-action
         3:delete"
    ::= { es2310cMacTableMacAliasEntry 4 }

es2310cGVRPInfo             OBJECT IDENTIFIER ::= { es2310cProduces 12 }

es2310cGvrpConf             OBJECT IDENTIFIER ::= { es2310cGVRPInfo 1 }

es2310cGvrpConfState OBJECT-TYPE
    SYNTAX      INTEGER(0|1)
    MAX-ACCESS      read-write
    STATUS      current
    DESCRIPTION
        "The state of GVRP.
         0 - Disable
         1 - Enable
    "
    ::= { es2310cGvrpConf 1 }

es2310cGvrpConfTable    OBJECT-TYPE
    SYNTAX      SEQUENCE OF ES2310CGvrpConfEntry
    MAX-ACCESS  not-accessible
    STATUS      current
    DESCRIPTION
        "This is a list of the GVRP conf table."
    ::= { es2310cGvrpConf 2 }

ES2310CGvrpConfEntry ::=
SEQUENCE {
    es2310cGvrpConfIndex             INTEGER,
    es2310cGvrpConfJoinTime          INTEGER,
    es2310cGvrpConfLeaveTime         INTEGER,
    es2310cGvrpConfLeaveAllTime      INTEGER,
    es2310cGvrpConfDefaultAppMode    INTEGER,
    es2310cGvrpConfDefaultRegMode    INTEGER,
    es2310cGvrpConfRestrictedMode    INTEGER
}

es2310cGvrpConfEntry    OBJECT-TYPE
    SYNTAX      ES2310CGvrpConfEntry
    MAX-ACCESS      not-accessible
    STATUS      current
    DESCRIPTION
        "Entry(s) for the GVRP conf table."
    INDEX {es2310cGvrpConfIndex}
    ::= { es2310cGvrpConfTable 1 }

es2310cGvrpConfIndex    OBJECT-TYPE
    SYNTAX      INTEGER(1..10)
    MAX-ACCESS      not-accessible
    STATUS      current
    DESCRIPTION
        "The index of the GVRP conf table."
    ::= { es2310cGvrpConfEntry 1 }

es2310cGvrpConfJoinTime OBJECT-TYPE
    SYNTAX      INTEGER(20..100)
    MAX-ACCESS      read-write
    STATUS      current
    DESCRIPTION
        "The join time of the GVRP entry.
         range: 20~100
         default 20 centisecond"
    ::= { es2310cGvrpConfEntry 2 }

es2310cGvrpConfLeaveTime    OBJECT-TYPE
    SYNTAX      INTEGER(60..300)
    MAX-ACCESS      read-write
    STATUS      current
    DESCRIPTION
        "The leave time of the GVRP entry.
         range: 60~300
        default:60 centisecond"
    ::= { es2310cGvrpConfEntry 3 }

es2310cGvrpConfLeaveAllTime OBJECT-TYPE
    SYNTAX      INTEGER(1000..5000)
    MAX-ACCESS      read-write
    STATUS      current
    DESCRIPTION
        "The leave all time of the GVRP entry.
         range: 1000~5000
         default: 1000 unit time"
    ::= { es2310cGvrpConfEntry 4 }

es2310cGvrpConfDefaultAppMode   OBJECT-TYPE
    SYNTAX      INTEGER(0|1)
    MAX-ACCESS      read-write
    STATUS      current
    DESCRIPTION
        "The default application mode of the GVRP entry.
         0 - Normal
         1 - Non-Participant
         default: Normal"
    ::= { es2310cGvrpConfEntry 5 }

es2310cGvrpConfDefaultRegMode   OBJECT-TYPE
    SYNTAX      INTEGER(0|1|2)
    MAX-ACCESS      read-write
    STATUS      current
    DESCRIPTION
        "The default registrar mode of the GVRP entry.
         0 - Normal
         1 - Fixed
         2 - Forbidden
         default: Normal"
    ::= { es2310cGvrpConfEntry 6 }

es2310cGvrpConfRestrictedMode   OBJECT-TYPE
    SYNTAX      INTEGER(0|1)
    MAX-ACCESS      read-write
    STATUS      current
    DESCRIPTION
        "The restricted mode of the GVRP entry.
         0 - Disable
         1 - Enable
         default: Disable"
    ::= { es2310cGvrpConfEntry 7 }

es2310cGvrpCounter              OBJECT IDENTIFIER ::= { es2310cGVRPInfo 2 }

es2310cGvrpCounterTable OBJECT-TYPE
    SYNTAX      SEQUENCE OF ES2310CGvrpCounterEntry
    MAX-ACCESS  not-accessible
    STATUS      current
    DESCRIPTION
        "This is a list of the GVRP counter table."
    ::= { es2310cGvrpCounter 1 }

ES2310CGvrpCounterEntry ::=
SEQUENCE {
    es2310cGvrpCounterIndex              INTEGER,
    es2310cGvrpCounterRxTotalGvrpPkts    Counter32,
    es2310cGvrpCounterRxInvalidGvrpPkts  Counter32,
    es2310cGvrpCounterRxLeaveAllMsg      Counter32,
    es2310cGvrpCounterRxJoinEmptyMsg     Counter32,
    es2310cGvrpCounterRxJoinInMsg        Counter32,
    es2310cGvrpCounterRxLeaveEmptyMsg    Counter32,
    es2310cGvrpCounterRxEmptyMsg         Counter32,
    es2310cGvrpCounterTxTotalGvrpPkts    Counter32,
    es2310cGvrpCounterTxLeaveAllMsg      Counter32,
    es2310cGvrpCounterTxJoinEmptyMsg     Counter32,
    es2310cGvrpCounterTxJoinInMsg        Counter32,
    es2310cGvrpCounterTxLeaveEmptyMsg    Counter32,
    es2310cGvrpCounterTxEmptyMsg         Counter32
}

es2310cGvrpCounterEntry OBJECT-TYPE
    SYNTAX      ES2310CGvrpCounterEntry
    MAX-ACCESS      not-accessible
    STATUS      current
    DESCRIPTION
        "Entry(s) for the GVRP counter table."
    INDEX {es2310cGvrpCounterIndex}
    ::= { es2310cGvrpCounterTable 1 }

es2310cGvrpCounterIndex OBJECT-TYPE
    SYNTAX      INTEGER(1..10)
    MAX-ACCESS      not-accessible
    STATUS      current
    DESCRIPTION
        "The port index of the GVRP counter table."
    ::= { es2310cGvrpCounterEntry 1 }

es2310cGvrpCounterRxTotalGvrpPkts   OBJECT-TYPE
    SYNTAX      Counter32
    MAX-ACCESS      read-only
    STATUS      current
    DESCRIPTION
        "This is Rx Total GVRP packet counters."
    ::= { es2310cGvrpCounterEntry 2 }

es2310cGvrpCounterRxInvalidGvrpPkts OBJECT-TYPE
    SYNTAX      Counter32
    MAX-ACCESS      read-only
    STATUS      current
    DESCRIPTION
        "This is Rx Invalid GVRP packet counters."
    ::= { es2310cGvrpCounterEntry 3 }

es2310cGvrpCounterRxLeaveAllMsg OBJECT-TYPE
    SYNTAX      Counter32
    MAX-ACCESS      read-only
    STATUS      current
    DESCRIPTION
        "This is Rx LeaveAll message packet counters."
    ::= { es2310cGvrpCounterEntry 4 }

es2310cGvrpCounterRxJoinEmptyMsg    OBJECT-TYPE
    SYNTAX      Counter32
    MAX-ACCESS      read-only
    STATUS      current
    DESCRIPTION
        "This is Rx JoinEmpty message packet counters."
    ::= { es2310cGvrpCounterEntry 5 }

es2310cGvrpCounterRxJoinInMsg   OBJECT-TYPE
    SYNTAX      Counter32
    MAX-ACCESS      read-only
    STATUS      current
    DESCRIPTION
        "This is Rx JoinIn message packet counters."
    ::= { es2310cGvrpCounterEntry 6 }

es2310cGvrpCounterRxLeaveEmptyMsg   OBJECT-TYPE
    SYNTAX      Counter32
    MAX-ACCESS      read-only
    STATUS      current
    DESCRIPTION
        "This is Rx LeaveEmpty message packet counters."
    ::= { es2310cGvrpCounterEntry 7 }

es2310cGvrpCounterRxEmptyMsg    OBJECT-TYPE
    SYNTAX      Counter32
    MAX-ACCESS      read-only
    STATUS      current
    DESCRIPTION
        "This is Rx Empty message packet counters."
    ::= { es2310cGvrpCounterEntry 8 }

es2310cGvrpCounterTxTotalGvrpPkts   OBJECT-TYPE
    SYNTAX      Counter32
    MAX-ACCESS      read-only
    STATUS      current
    DESCRIPTION
        "This is Tx Total GVRP packet counters."
    ::= { es2310cGvrpCounterEntry 9 }

es2310cGvrpCounterTxLeaveAllMsg OBJECT-TYPE
    SYNTAX      Counter32
    MAX-ACCESS      read-only
    STATUS      current
    DESCRIPTION
        "This is Tx LeaveAll message packet counters."
    ::= { es2310cGvrpCounterEntry 10 }

es2310cGvrpCounterTxJoinEmptyMsg    OBJECT-TYPE
    SYNTAX      Counter32
    MAX-ACCESS      read-only
    STATUS      current
    DESCRIPTION
        "This is Tx JoinEmpty message packet counters."
    ::= { es2310cGvrpCounterEntry 11 }

es2310cGvrpCounterTxJoinInMsg   OBJECT-TYPE
    SYNTAX      Counter32
    MAX-ACCESS      read-only
    STATUS      current
    DESCRIPTION
        "This is Tx JoinIn message packet counters."
    ::= { es2310cGvrpCounterEntry 12 }

es2310cGvrpCounterTxLeaveEmptyMsg   OBJECT-TYPE
    SYNTAX      Counter32
    MAX-ACCESS      read-only
    STATUS      current
    DESCRIPTION
        "This is Tx LeaveEmpty message packet counters."
    ::= { es2310cGvrpCounterEntry 13 }

es2310cGvrpCounterTxEmptyMsg    OBJECT-TYPE
    SYNTAX      Counter32
    MAX-ACCESS      read-only
    STATUS      current
    DESCRIPTION
        "This is Tx Empty message packet counters."
    ::= { es2310cGvrpCounterEntry 14 }

es2310cGvrpGroup            OBJECT IDENTIFIER ::= { es2310cGVRPInfo 3 }

es2310cGvrpGroupNumber  OBJECT-TYPE
    SYNTAX      INTEGER(0..4094)
    MAX-ACCESS      read-only
    STATUS      current
    DESCRIPTION
        "This is number of the GVRP group table entry."
    ::= { es2310cGvrpGroup 1 }

es2310cGvrpGroupTable   OBJECT-TYPE
    SYNTAX      SEQUENCE OF ES2310CGvrpGroupEntry
    MAX-ACCESS  not-accessible
    STATUS      current
    DESCRIPTION
        "This is a list of the GVRP group table."
    ::= { es2310cGvrpGroup 2 }

ES2310CGvrpGroupEntry ::=
SEQUENCE {
    es2310cGvrpGroupId            INTEGER,
    es2310cGvrpGroupVid           INTEGER,
    es2310cGvrpGroupMemberPort    DisplayString
}

es2310cGvrpGroupEntry   OBJECT-TYPE
    SYNTAX      ES2310CGvrpGroupEntry
    MAX-ACCESS      not-accessible
    STATUS      current
    DESCRIPTION
        "Entry(s) for the GVRP group table."
    INDEX {es2310cGvrpGroupId}
    ::= { es2310cGvrpGroupTable 1 }

es2310cGvrpGroupId  OBJECT-TYPE
    SYNTAX      INTEGER(1..4094)
    MAX-ACCESS      read-only
    STATUS      current
    DESCRIPTION
        "The index of the GVRP group table."
    ::= { es2310cGvrpGroupEntry 1 }

es2310cGvrpGroupVid OBJECT-TYPE
    SYNTAX      INTEGER(1..4094)
    MAX-ACCESS      read-only
    STATUS      current
    DESCRIPTION
        "This is vid of GVRP group."
    ::= { es2310cGvrpGroupEntry 2 }

es2310cGvrpGroupMemberPort  OBJECT-TYPE
    SYNTAX      DisplayString
    MAX-ACCESS      read-only
    STATUS      current
    DESCRIPTION
        "This is the member port of GVRP group."
    ::= { es2310cGvrpGroupEntry 3 }

es2310cSecurity             OBJECT IDENTIFIER ::= { es2310cProduces 13 }

es2310cIsolatedPortGroup OBJECT-TYPE
    SYNTAX      DisplayString
    MAX-ACCESS      read-write
    STATUS      current
    DESCRIPTION
        "This is isolated group.
         0: Disable"
    ::= { es2310cSecurity 1 }

es2310cMirror               OBJECT IDENTIFIER ::= { es2310cSecurity 2 }

es2310cMirrorMode OBJECT-TYPE
    SYNTAX      INTEGER(0|1)
    MAX-ACCESS      read-write
    STATUS      current
    DESCRIPTION
        "This is mirror mode.
         0 - Disable
         1 - Enable
    "
    ::= { es2310cMirror 1 }

es2310cMonitoringPort OBJECT-TYPE
    SYNTAX      INTEGER(1..10)
    MAX-ACCESS      read-write
    STATUS      current
    DESCRIPTION
        "This is monitoring port."
    ::= { es2310cMirror 2 }

es2310cMonitoredIngressPort OBJECT-TYPE
    SYNTAX      DisplayString
    MAX-ACCESS      read-write
    STATUS      current
    DESCRIPTION
        "This is monitored ingress ports."
    ::= { es2310cMirror 3 }

es2310cMonitoredEgressPort OBJECT-TYPE
    SYNTAX      DisplayString
    MAX-ACCESS      read-write
    STATUS      current
    DESCRIPTION
        "This is monitored egress ports."
    ::= { es2310cMirror 4 }

es2310cVirtualStack        OBJECT IDENTIFIER ::= { es2310cProduces 14 }

es2310cVirtualStackState   OBJECT-TYPE
    SYNTAX      INTEGER(0|1)
    MAX-ACCESS  read-write
    STATUS      current
    DESCRIPTION
        "Set the Virtual Stack State.
         0 : disable,
         1 : enable
        "
    ::= { es2310cVirtualStack 1 }

es2310cVirtualStackRole   OBJECT-TYPE
    SYNTAX      INTEGER(0|1)
    MAX-ACCESS  read-write
    STATUS      current
    DESCRIPTION
        "Set the Virtual Stack Role.
         0 : slave,
         1 : master
        "
    ::= { es2310cVirtualStack 2 }

es2310cVirtualStackGroupID  OBJECT-TYPE
    SYNTAX      DisplayString
    MAX-ACCESS  read-write
    STATUS      current
    DESCRIPTION
        "Set the Virtual Stack Group ID."
    ::= { es2310cVirtualStack 3 }

es2310cManagementSecurity               OBJECT IDENTIFIER ::= { es2310cProduces 15 }

es2310cManagementSecurityNumber OBJECT-TYPE
    SYNTAX      INTEGER(0..64)
    MAX-ACCESS      read-only
    STATUS      current
    DESCRIPTION
        "This is number of the management security table entry."
    ::= { es2310cManagementSecurity 1 }

es2310cManagementSecurityEntryCreate OBJECT-TYPE
    SYNTAX      INTEGER(0..64)
    MAX-ACCESS      read-write
    STATUS      current
    DESCRIPTION
        "Creat a management security entry.
         Set 1: add a new entry,
         Get: the number means index."
    ::= { es2310cManagementSecurity 2 }

es2310cManagementSecurityTable  OBJECT-TYPE
    SYNTAX      SEQUENCE OF ES2310CManagementSecurityEntry
    MAX-ACCESS  not-accessible
    STATUS      current
    DESCRIPTION
        "This is a list of the management security table."
    ::= { es2310cManagementSecurity 3 }

ES2310CManagementSecurityEntry ::=
SEQUENCE {
    es2310cManagementSecurityIndex          INTEGER,
    es2310cManagementSecurityName           DisplayString,
    es2310cManagementSecurityVid            INTEGER,
    es2310cManagementSecurityIpRange        DisplayString,
    es2310cManagementSecurityIncomigPort    DisplayString,
    es2310cManagementSecurityAccessType     DisplayString,
    es2310cManagementSecurityAction         INTEGER,
    es2310cManagementSecurityEntryAction    INTEGER
}

es2310cManagementSecurityEntry  OBJECT-TYPE
    SYNTAX      ES2310CManagementSecurityEntry
    MAX-ACCESS      not-accessible
    STATUS      current
    DESCRIPTION
        "Entry(s) for the management security table."
    INDEX {es2310cManagementSecurityIndex}
    ::= { es2310cManagementSecurityTable 1 }

es2310cManagementSecurityIndex  OBJECT-TYPE
    SYNTAX      INTEGER(1..64)
    MAX-ACCESS      not-accessible
    STATUS      current
    DESCRIPTION
        "The index of the management security table."
    ::= { es2310cManagementSecurityEntry 1 }

es2310cManagementSecurityName   OBJECT-TYPE
    SYNTAX      DisplayString
    MAX-ACCESS      read-write
    STATUS      current
    DESCRIPTION
        "The name of the management security entry."
    ::= { es2310cManagementSecurityEntry 2 }

es2310cManagementSecurityVid    OBJECT-TYPE
    SYNTAX      INTEGER(0..4094)
    MAX-ACCESS      read-write
    STATUS      current
    DESCRIPTION
        "This is the vid of the management security entry.
         0: any VID."
    ::= { es2310cManagementSecurityEntry 3 }

es2310cManagementSecurityIpRange    OBJECT-TYPE
    SYNTAX      DisplayString
    MAX-ACCESS      read-write
    STATUS      current
    DESCRIPTION
        "This is the IP range of the management security entry.
         0: any IP."
    ::= { es2310cManagementSecurityEntry 4 }

es2310cManagementSecurityIncomigPort    OBJECT-TYPE
    SYNTAX      DisplayString
    MAX-ACCESS      read-write
    STATUS      current
    DESCRIPTION
        "This is the ports of the management security entry.
         0: any incoming port."
    ::= { es2310cManagementSecurityEntry 5 }

es2310cManagementSecurityAccessType OBJECT-TYPE
    SYNTAX      DisplayString
    MAX-ACCESS      read-write
    STATUS      current
    DESCRIPTION
        "This is the access type of the management security entry.
         for example: http,snmp,telnet
         for example: http,telnet
         for example: any
         any means http,snmp and telnet."
    ::= { es2310cManagementSecurityEntry 6 }

es2310cManagementSecurityAction OBJECT-TYPE
    SYNTAX      INTEGER(0|1)
    MAX-ACCESS      read-write
    STATUS      current
    DESCRIPTION
        "This is the action of the management security entry.
         0:deny
         1:accept"
    ::= { es2310cManagementSecurityEntry 7 }

es2310cManagementSecurityEntryAction    OBJECT-TYPE
    SYNTAX      INTEGER(0..3)
    MAX-ACCESS      read-write
    STATUS      current
    DESCRIPTION
        "The action the management security entry.
         1:action
         2:non-action
         3:delete"
    ::= { es2310cManagementSecurityEntry 8 }

es2310cQoS              OBJECT IDENTIFIER ::= { es2310cProduces 16 }

es2310cQoSGlobalConfig              OBJECT IDENTIFIER ::= { es2310cQoS 1 }

es2310cQoSMode OBJECT-TYPE
    SYNTAX      INTEGER(0|1)
    MAX-ACCESS      read-write
    STATUS      current
    DESCRIPTION
        "The mode of QoS.
         0 - Disable
         1 - Enable
    "
    ::= { es2310cQoSGlobalConfig 1 }

es2310cQosPriorityControl1p OBJECT-TYPE
    SYNTAX      INTEGER(0|1)
    MAX-ACCESS      read-write
    STATUS      current
    DESCRIPTION
        "This is the priority control for 802.1p.
         0 - Disable
         1 - Enable
    "
    ::= { es2310cQoSGlobalConfig 2 }

es2310cQosPriorityControlTOS OBJECT-TYPE
    SYNTAX      INTEGER(0|1)
    MAX-ACCESS      read-write
    STATUS      current
    DESCRIPTION
        "This is the priority control for TOS.
         0 - Disable
         1 - Enable
    "
    ::= { es2310cQoSGlobalConfig 3 }

es2310cQosPriorityControlDSCP OBJECT-TYPE
    SYNTAX      INTEGER(0|1)
    MAX-ACCESS      read-write
    STATUS      current
    DESCRIPTION
        "This is the priority control for DSCP.
         0 - Disable
         1 - Enable
    "
    ::= { es2310cQoSGlobalConfig 4 }

es2310cQoSSchedulingMethod OBJECT-TYPE
    SYNTAX      INTEGER(0|1)
    MAX-ACCESS      read-write
    STATUS      current
    DESCRIPTION
        "This is the scheduling method.
         0 - WRR
         1 - Strict
    "
    ::= { es2310cQoSGlobalConfig 5 }

es2310cQoSWeightQ0 OBJECT-TYPE
    SYNTAX      INTEGER(1..55)
    MAX-ACCESS      read-write
    STATUS      current
    DESCRIPTION
        "This is the weigtht of Queue0."
    ::= { es2310cQoSGlobalConfig 6 }

es2310cQoSWeightQ1 OBJECT-TYPE
    SYNTAX      INTEGER(1..55)
    MAX-ACCESS      read-write
    STATUS      current
    DESCRIPTION
        "This is the weigtht of Queue1."
    ::= { es2310cQoSGlobalConfig 7 }

es2310cQoSWeightQ2 OBJECT-TYPE
    SYNTAX      INTEGER(1..55)
    MAX-ACCESS      read-write
    STATUS      current
    DESCRIPTION
        "This is the weigtht of Queue2."
    ::= { es2310cQoSGlobalConfig 8 }

es2310cQoSWeightQ3 OBJECT-TYPE
    SYNTAX      INTEGER(1..55)
    MAX-ACCESS      read-write
    STATUS      current
    DESCRIPTION
        "This is the weigtht of Queue3."
    ::= { es2310cQoSGlobalConfig 9 }

es2310cQoSVIPPort OBJECT-TYPE
    SYNTAX      DisplayString
    MAX-ACCESS      read-write
    STATUS      current
    DESCRIPTION
        "This is the VIP group for QoS."
    ::= { es2310cQoS 2 }

es2310cQoS1pPriority            OBJECT IDENTIFIER ::= { es2310cQoS 3 }

es2310cQoS1pPriorityTable   OBJECT-TYPE
    SYNTAX      SEQUENCE OF ES2310CQoS1pPriorityEntry
    MAX-ACCESS  not-accessible
    STATUS      current
    DESCRIPTION
        "This is a list of the 802.1p."
    ::= { es2310cQoS1pPriority 1 }

ES2310CQoS1pPriorityEntry ::=
SEQUENCE {
    es2310cQoS1pPriorityIndex    INTEGER,
    es2310cQoS1pPriorityValue    INTEGER,
    es2310cQoS1pPriorityQueue    INTEGER
}

es2310cQoS1pPriorityEntry   OBJECT-TYPE
    SYNTAX      ES2310CQoS1pPriorityEntry
    MAX-ACCESS      not-accessible
    STATUS      current
    DESCRIPTION
        "Entry(s) for the 802.1p priority table."
    INDEX {es2310cQoS1pPriorityIndex}
    ::= { es2310cQoS1pPriorityTable 1 }

es2310cQoS1pPriorityIndex   OBJECT-TYPE
    SYNTAX      INTEGER(1..8)
    MAX-ACCESS      not-accessible
    STATUS      current
    DESCRIPTION
        "The index of the 802.1p priority table."
    ::= { es2310cQoS1pPriorityEntry 1 }

es2310cQoS1pPriorityValue   OBJECT-TYPE
    SYNTAX      INTEGER(0..7)
    MAX-ACCESS      read-only
    STATUS      current
    DESCRIPTION
        "The value of 802.1p priority entry."
    ::= { es2310cQoS1pPriorityEntry 2 }

es2310cQoS1pPriorityQueue   OBJECT-TYPE
    SYNTAX      INTEGER(0..3)
    MAX-ACCESS      read-write
    STATUS      current
    DESCRIPTION
        "The queue of 802.1p priority entry."
    ::= { es2310cQoS1pPriorityEntry 3 }

es2310cQoSDTypeTOSPriority              OBJECT IDENTIFIER ::= { es2310cQoS 4 }

es2310cQoSDTypeTOSPriorityTable OBJECT-TYPE
    SYNTAX      SEQUENCE OF ES2310CQoSDTypeTOSPriorityEntry
    MAX-ACCESS  not-accessible
    STATUS      current
    DESCRIPTION
        "This is a list of the TOS delay priority mapping entry."
    ::= { es2310cQoSDTypeTOSPriority 1 }

ES2310CQoSDTypeTOSPriorityEntry ::=
SEQUENCE {
    es2310cQoSDTypeTOSPriorityIndex    INTEGER,
    es2310cQoSDTypeTOSPriorityValue    INTEGER,
    es2310cQoSDTypeTOSPriorityQueue    INTEGER
}

es2310cQoSDTypeTOSPriorityEntry OBJECT-TYPE
    SYNTAX      ES2310CQoSDTypeTOSPriorityEntry
    MAX-ACCESS      not-accessible
    STATUS      current
    DESCRIPTION
        "Entry(s) for the ToS delay priority mapping entry."
    INDEX {es2310cQoSDTypeTOSPriorityIndex}
    ::= { es2310cQoSDTypeTOSPriorityTable 1 }

es2310cQoSDTypeTOSPriorityIndex OBJECT-TYPE
    SYNTAX      INTEGER(1..8)
    MAX-ACCESS      not-accessible
    STATUS      current
    DESCRIPTION
        "The index of the ToS delay priority mapping table."
    ::= { es2310cQoSDTypeTOSPriorityEntry 1 }

es2310cQoSDTypeTOSPriorityValue OBJECT-TYPE
    SYNTAX      INTEGER(0..7)
    MAX-ACCESS      read-only
    STATUS      current
    DESCRIPTION
        "The value of ToS delay priority mapping entry."
    ::= { es2310cQoSDTypeTOSPriorityEntry 2 }

es2310cQoSDTypeTOSPriorityQueue OBJECT-TYPE
    SYNTAX      INTEGER(0..3)
    MAX-ACCESS      read-write
    STATUS      current
    DESCRIPTION
        "The queue of ToS delay priority mapping entry."
    ::= { es2310cQoSDTypeTOSPriorityEntry 3 }

es2310cQoSTTypeTOSPriority              OBJECT IDENTIFIER ::= { es2310cQoS 5 }

es2310cQoSTTypeTOSPriorityTable OBJECT-TYPE
    SYNTAX      SEQUENCE OF ES2310CQoSTTypeTOSPriorityEntry
    MAX-ACCESS  not-accessible
    STATUS      current
    DESCRIPTION
        "This is a list of the ToS throughput priority mapping entry."
    ::= { es2310cQoSTTypeTOSPriority 1 }

ES2310CQoSTTypeTOSPriorityEntry ::=
SEQUENCE {
    es2310cQoSTTypeTOSPriorityIndex    INTEGER,
    es2310cQoSTTypeTOSPriorityValue    INTEGER,
    es2310cQoSTTypeTOSPriorityQueue    INTEGER
}

es2310cQoSTTypeTOSPriorityEntry OBJECT-TYPE
    SYNTAX      ES2310CQoSTTypeTOSPriorityEntry
    MAX-ACCESS      not-accessible
    STATUS      current
    DESCRIPTION
        "Entry(s) for the TOS Throughput mapping entry."
    INDEX {es2310cQoSTTypeTOSPriorityIndex}
    ::= { es2310cQoSTTypeTOSPriorityTable 1 }

es2310cQoSTTypeTOSPriorityIndex OBJECT-TYPE
    SYNTAX      INTEGER(1..8)
    MAX-ACCESS      not-accessible
    STATUS      current
    DESCRIPTION
        "The index of the TOS throughput priority mapping table."
    ::= { es2310cQoSTTypeTOSPriorityEntry 1 }

es2310cQoSTTypeTOSPriorityValue OBJECT-TYPE
    SYNTAX      INTEGER(0..7)
    MAX-ACCESS      read-only
    STATUS      current
    DESCRIPTION
        "The value of TOS throughput priority mapping entry."
    ::= { es2310cQoSTTypeTOSPriorityEntry 2 }

es2310cQoSTTypeTOSPriorityQueue OBJECT-TYPE
    SYNTAX      INTEGER(0..3)
    MAX-ACCESS      read-write
    STATUS      current
    DESCRIPTION
        "The queue of TOS throughput priority mapping entry."
    ::= { es2310cQoSTTypeTOSPriorityEntry 3 }

es2310cQoSRTypeTOSPriority              OBJECT IDENTIFIER ::= { es2310cQoS 6 }

es2310cQoSRTypeTOSPriorityTable OBJECT-TYPE
    SYNTAX      SEQUENCE OF ES2310CQoSRTypeTOSPriorityEntry
    MAX-ACCESS  not-accessible
    STATUS      current
    DESCRIPTION
        "This is a list of the ToS reliability priority mapping entry."
    ::= { es2310cQoSRTypeTOSPriority 1 }

ES2310CQoSRTypeTOSPriorityEntry ::=
SEQUENCE {
    es2310cQoSRTypeTOSPriorityIndex    INTEGER,
    es2310cQoSRTypeTOSPriorityValue    INTEGER,
    es2310cQoSRTypeTOSPriorityQueue    INTEGER
}

es2310cQoSRTypeTOSPriorityEntry OBJECT-TYPE
    SYNTAX      ES2310CQoSRTypeTOSPriorityEntry
    MAX-ACCESS      not-accessible
    STATUS      current
    DESCRIPTION
        "Entry(s) for the TOS reliability mapping entry."
    INDEX {es2310cQoSRTypeTOSPriorityIndex}
    ::= { es2310cQoSRTypeTOSPriorityTable 1 }

es2310cQoSRTypeTOSPriorityIndex OBJECT-TYPE
    SYNTAX      INTEGER(1..8)
    MAX-ACCESS      not-accessible
    STATUS      current
    DESCRIPTION
        "The index of the TOS reliability priority mapping table."
    ::= { es2310cQoSRTypeTOSPriorityEntry 1 }

es2310cQoSRTypeTOSPriorityValue OBJECT-TYPE
    SYNTAX      INTEGER(0..7)
    MAX-ACCESS      read-only
    STATUS      current
    DESCRIPTION
        "The value of TOS reliability priority mapping entry."
    ::= { es2310cQoSRTypeTOSPriorityEntry 2 }

es2310cQoSRTypeTOSPriorityQueue OBJECT-TYPE
    SYNTAX      INTEGER(0..3)
    MAX-ACCESS      read-write
    STATUS      current
    DESCRIPTION
        "The queue of TOS reliability priority mapping entry."
    ::= { es2310cQoSRTypeTOSPriorityEntry 3 }

es2310cQoSMTypeTOSPriority              OBJECT IDENTIFIER ::= { es2310cQoS 7 }

es2310cQoSMTypeTOSPriorityTable OBJECT-TYPE
    SYNTAX      SEQUENCE OF ES2310CQoSMTypeTOSPriorityEntry
    MAX-ACCESS  not-accessible
    STATUS      current
    DESCRIPTION
        "This is a list of the ToS monetary cost priority mapping entry."
    ::= { es2310cQoSMTypeTOSPriority 1 }

ES2310CQoSMTypeTOSPriorityEntry ::=
SEQUENCE {
    es2310cQoSMTypeTOSPriorityIndex    INTEGER,
    es2310cQoSMTypeTOSPriorityValue    INTEGER,
    es2310cQoSMTypeTOSPriorityQueue    INTEGER
}

es2310cQoSMTypeTOSPriorityEntry OBJECT-TYPE
    SYNTAX      ES2310CQoSMTypeTOSPriorityEntry
    MAX-ACCESS      not-accessible
    STATUS      current
    DESCRIPTION
        "Entry(s) for the TOS monetary cost mapping entry."
    INDEX {es2310cQoSMTypeTOSPriorityIndex}
    ::= { es2310cQoSMTypeTOSPriorityTable 1 }

es2310cQoSMTypeTOSPriorityIndex OBJECT-TYPE
    SYNTAX      INTEGER(1..8)
    MAX-ACCESS      not-accessible
    STATUS      current
    DESCRIPTION
        "The index of the TOS monetary cost priority mapping table."
    ::= { es2310cQoSMTypeTOSPriorityEntry 1 }

es2310cQoSMTypeTOSPriorityValue OBJECT-TYPE
    SYNTAX      INTEGER(0..7)
    MAX-ACCESS      read-only
    STATUS      current
    DESCRIPTION
        "The value of TOS monetary cost priority mapping entry."
    ::= { es2310cQoSMTypeTOSPriorityEntry 2 }

es2310cQoSMTypeTOSPriorityQueue OBJECT-TYPE
    SYNTAX      INTEGER(0..3)
    MAX-ACCESS      read-write
    STATUS      current
    DESCRIPTION
        "The queue of TOS monetary cost priority mapping entry."
    ::= { es2310cQoSMTypeTOSPriorityEntry 3 }

es2310cQoSDSCPPriority              OBJECT IDENTIFIER ::= { es2310cQoS 8 }

es2310cQoSDSCPPriorityTable OBJECT-TYPE
    SYNTAX      SEQUENCE OF ES2310CQoSDSCPPriorityEntry
    MAX-ACCESS  not-accessible
    STATUS      current
    DESCRIPTION
        "This is a list of the DSCP priority entry."
    ::= { es2310cQoSDSCPPriority 1 }

ES2310CQoSDSCPPriorityEntry ::=
SEQUENCE {
    es2310cQoSDSCPPriorityIndex    INTEGER,
    es2310cQoSDSCPPriorityValue    INTEGER,
    es2310cQoSDSCPPriorityQueue    INTEGER
}

es2310cQoSDSCPPriorityEntry OBJECT-TYPE
    SYNTAX      ES2310CQoSDSCPPriorityEntry
    MAX-ACCESS      not-accessible
    STATUS      current
    DESCRIPTION
        "Entry(s) for the DSCP priority mapping entry."
    INDEX {es2310cQoSDSCPPriorityIndex}
    ::= { es2310cQoSDSCPPriorityTable 1 }

es2310cQoSDSCPPriorityIndex OBJECT-TYPE
    SYNTAX      INTEGER(1..64)
    MAX-ACCESS      not-accessible
    STATUS      current
    DESCRIPTION
        "The index of the DSCP priority priority mapping table."
    ::= { es2310cQoSDSCPPriorityEntry 1 }

es2310cQoSDSCPPriorityValue OBJECT-TYPE
    SYNTAX      INTEGER(0..63)
    MAX-ACCESS      read-only
    STATUS      current
    DESCRIPTION
        "The value of DSCP priority priority mapping entry."
    ::= { es2310cQoSDSCPPriorityEntry 2 }

es2310cQoSDSCPPriorityQueue OBJECT-TYPE
    SYNTAX      INTEGER(0..3)
    MAX-ACCESS      read-write
    STATUS      current
    DESCRIPTION
        "The queue of DSCP priority priority mapping entry."
    ::= { es2310cQoSDSCPPriorityEntry 3 }

es2310cVlan      OBJECT IDENTIFIER ::= { es2310cProduces 17 }

es2310cVlanModeConfig      OBJECT IDENTIFIER ::= { es2310cVlan 1 }

es2310cVlanMode  OBJECT-TYPE
    SYNTAX      INTEGER(0..2)
    MAX-ACCESS  read-write
    STATUS      current
    DESCRIPTION
        "0:Tag-based, 1:Port-based, 2:Metro mode"
    ::= { es2310cVlanModeConfig 1 }

es2310cSymmetricVlan  OBJECT-TYPE
    SYNTAX      INTEGER(0|1)
    MAX-ACCESS  read-write
    STATUS      current
    DESCRIPTION
        "Symmetric VLAN: for tag-based
        0:disable, 1:enable"
    ::= { es2310cVlanModeConfig 2 }

es2310cVlanSVL  OBJECT-TYPE
    SYNTAX      INTEGER(0|1)
    MAX-ACCESS  read-write
    STATUS      current
    DESCRIPTION
        "SVL: : for tag-based
        0:disable, 1:enable"
    ::= { es2310cVlanModeConfig 3 }

es2310cDoubleTag  OBJECT-TYPE
    SYNTAX      INTEGER(0|1)
    MAX-ACCESS  read-write
    STATUS      current
    DESCRIPTION
        "Double Tag: for tag-based
        0:disable, 1:enable"
    ::= { es2310cVlanModeConfig 4 }

es2310cUpLinkPort  OBJECT-TYPE
    SYNTAX      INTEGER(0..2)
    MAX-ACCESS  read-write
    STATUS      current
    DESCRIPTION
        "Up link Port: for Metro mode
        0:Port 9, 1:Port 10, 2:Port 9 & 10"
    ::= { es2310cVlanModeConfig 5 }

es2310cTagBasedVlanGroup      OBJECT IDENTIFIER ::= { es2310cVlan 2 }

es2310cTagBasedVlanNumbers  OBJECT-TYPE
    SYNTAX      INTEGER(1..4094)
    MAX-ACCESS  read-only
    STATUS      current
    DESCRIPTION
        "Total numbers for tag-based vlan."
    ::= { es2310cTagBasedVlanGroup 1 }

es2310cTagBasedCreateStatus  OBJECT-TYPE
    SYNTAX      INTEGER(0..4094)
    MAX-ACCESS  read-write
    STATUS      current
    DESCRIPTION
        "Creat a temp vlan in tag-based vlan table.
         0 : none,
         1~4094 : creat with this vid.
        "
    ::= { es2310cTagBasedVlanGroup 2 }

es2310cTagBasedVlanTable  OBJECT-TYPE
    SYNTAX      SEQUENCE OF ES2310CTagBasedVlanEntry
    MAX-ACCESS  not-accessible
    STATUS      current
    DESCRIPTION
        " "
    ::= { es2310cTagBasedVlanGroup 3 }

ES2310CTagBasedVlanEntry ::=
SEQUENCE {
    es2310cTagBasedVlanVid              INTEGER,
    es2310cTagBasedVlanName                 DisplayString,
    es2310cTagBasedVlanMember               DisplayString,
    es2310cTagBasedVlanUntag                DisplayString,
    es2310cTagBasedVlanRowStatus                INTEGER
}

es2310cTagBasedVlanEntry OBJECT-TYPE
    SYNTAX      ES2310CTagBasedVlanEntry
    MAX-ACCESS  not-accessible
    STATUS      current
    DESCRIPTION
        "Entry(s) for tag-based vlan table."
    INDEX {es2310cTagBasedVlanVid}
    ::= { es2310cTagBasedVlanTable 1 }

es2310cTagBasedVlanVid  OBJECT-TYPE
    SYNTAX      INTEGER(1..4094)
    MAX-ACCESS  not-accessible
    STATUS      current
    DESCRIPTION
        "The vid of vlan."
    ::= { es2310cTagBasedVlanEntry 1 }

es2310cTagBasedVlanName  OBJECT-TYPE
    SYNTAX      DisplayString
    MAX-ACCESS  read-write
    STATUS      current
    DESCRIPTION
        "The name of vlan."
    ::= { es2310cTagBasedVlanEntry 2 }

es2310cTagBasedVlanMember  OBJECT-TYPE
    SYNTAX      DisplayString
    MAX-ACCESS  read-write
    STATUS      current
    DESCRIPTION
        "The member of vlan."
    ::= { es2310cTagBasedVlanEntry 3 }

es2310cTagBasedVlanUntag  OBJECT-TYPE
    SYNTAX      DisplayString
    MAX-ACCESS  read-write
    STATUS      current
    DESCRIPTION
        "The untag port of vlan."
    ::= { es2310cTagBasedVlanEntry 4 }

es2310cTagBasedVlanRowStatus  OBJECT-TYPE
    SYNTAX      INTEGER(1..3)
    MAX-ACCESS  read-write
    STATUS      current
    DESCRIPTION
        "The row status of vlan.
         1 : active,
         2 : not-inService,
         3 : delete
        "
    ::= { es2310cTagBasedVlanEntry 5 }

es2310cVlanPvid      OBJECT IDENTIFIER ::= { es2310cVlan 3 }

es2310cVlanPvidTable  OBJECT-TYPE
    SYNTAX      SEQUENCE OF ES2310CVlanPvidEntry
    MAX-ACCESS  not-accessible
    STATUS      current
    DESCRIPTION
        " "
    ::= { es2310cVlanPvid 1 }

ES2310CVlanPvidEntry ::=
SEQUENCE {
    es2310cVlanPvidPort             INTEGER,
    es2310cVlanPvidValue            INTEGER,
    es2310cVlanPvidDefaultPriority              INTEGER,
    es2310cVlanPvidDropUntag            INTEGER
}

es2310cVlanPvidEntry OBJECT-TYPE
    SYNTAX      ES2310CVlanPvidEntry
    MAX-ACCESS  not-accessible
    STATUS      current
    DESCRIPTION
        "Entry(s) for Vlan Pvid."
    INDEX {es2310cVlanPvidPort}
    ::= { es2310cVlanPvidTable 1 }

es2310cVlanPvidPort  OBJECT-TYPE
    SYNTAX      INTEGER(1..10)
    MAX-ACCESS  not-accessible
    STATUS      current
    DESCRIPTION
        "The port number of pvid entry."
    ::= { es2310cVlanPvidEntry 1 }

es2310cVlanPvidValue  OBJECT-TYPE
    SYNTAX      INTEGER(1..4094)
    MAX-ACCESS  read-write
    STATUS      current
    DESCRIPTION
        "The pvid value of port."
    ::= { es2310cVlanPvidEntry 2 }

es2310cVlanPvidDefaultPriority  OBJECT-TYPE
    SYNTAX      INTEGER(0..7)
    MAX-ACCESS  read-write
    STATUS      current
    DESCRIPTION
        "The default priority of port ."
    ::= { es2310cVlanPvidEntry 3 }

es2310cVlanPvidDropUntag  OBJECT-TYPE
    SYNTAX      INTEGER(0..7)
    MAX-ACCESS  read-write
    STATUS      current
    DESCRIPTION
        "The drop untag of port ."
    ::= { es2310cVlanPvidEntry 4 }

es2310cPortBasedVlanGroup      OBJECT IDENTIFIER ::= { es2310cVlan 4 }

es2310cPortBasedVlanNumbers  OBJECT-TYPE
    SYNTAX      INTEGER(1..10)
    MAX-ACCESS  read-only
    STATUS      current
    DESCRIPTION
        "Total numbers for tag-based vlan."
    ::= { es2310cPortBasedVlanGroup 1 }

es2310cPortBasedCreateStatus  OBJECT-TYPE
    SYNTAX      INTEGER(0|1)
    MAX-ACCESS  read-write
    STATUS      current
    DESCRIPTION
        "Creat a temp vlan in port-based vlan table.
         0 : none,
         1 : creat a new port-based vlan.
        "
    ::= { es2310cPortBasedVlanGroup 2 }

es2310cPortBasedVlanTable  OBJECT-TYPE
    SYNTAX      SEQUENCE OF ES2310CPortBasedVlanEntry
    MAX-ACCESS  not-accessible
    STATUS      current
    DESCRIPTION
        " "
    ::= { es2310cPortBasedVlanGroup 3 }

ES2310CPortBasedVlanEntry ::=
SEQUENCE {
    es2310cPortBasedVlanIndex               INTEGER,
    es2310cPortBasedVlanName                DisplayString,
    es2310cPortBasedVlanMember                  DisplayString,
    es2310cPortBasedVlanRowStatus           INTEGER
}

es2310cPortBasedVlanEntry OBJECT-TYPE
    SYNTAX      ES2310CPortBasedVlanEntry
    MAX-ACCESS  not-accessible
    STATUS      current
    DESCRIPTION
        "Entry(s) for port-based vlan table."
    INDEX {es2310cPortBasedVlanIndex}
    ::= { es2310cPortBasedVlanTable 1 }

es2310cPortBasedVlanIndex  OBJECT-TYPE
    SYNTAX      INTEGER(1..10)
    MAX-ACCESS  not-accessible
    STATUS      current
    DESCRIPTION
        "The index of vlan."
    ::= { es2310cPortBasedVlanEntry 1 }

es2310cPortBasedVlanName  OBJECT-TYPE
    SYNTAX      DisplayString
    MAX-ACCESS  read-write
    STATUS      current
    DESCRIPTION
        "The name of vlan."
    ::= { es2310cPortBasedVlanEntry 2 }

es2310cPortBasedVlanMember  OBJECT-TYPE
    SYNTAX      DisplayString
    MAX-ACCESS  read-write
    STATUS      current
    DESCRIPTION
        "The member of vlan."
    ::= { es2310cPortBasedVlanEntry 3 }

es2310cPortBasedVlanRowStatus  OBJECT-TYPE
    SYNTAX      INTEGER(1..3)
    MAX-ACCESS  read-write
    STATUS      current
    DESCRIPTION
        "The row status of vlan.
         1 : active,
         2 : not-inService,
         3 : delete
        "
    ::= { es2310cPortBasedVlanEntry 4 }

es2310cManagementVlan      OBJECT IDENTIFIER ::= { es2310cVlan 5 }

es2310cManagementVlanState  OBJECT-TYPE
    SYNTAX      INTEGER(0|1)
    MAX-ACCESS  read-write
    STATUS      current
    DESCRIPTION
        "The stat of management vlan. (for tag-base)
         0 : Disable,
         1 : Enable.
        "
    ::= { es2310cManagementVlan 1 }

es2310cManagementVlanVid  OBJECT-TYPE
    SYNTAX      INTEGER(1..4094)
    MAX-ACCESS  read-write
    STATUS      current
    DESCRIPTION
        "The vid value of management vlan."
    ::= { es2310cManagementVlan 2 }

es2310cDot1X        OBJECT IDENTIFIER ::= { es2310cProduces 18 }

es2310cDot1XStateSetting      OBJECT IDENTIFIER ::= { es2310cDot1X 1 }

es2310cRadiusServer OBJECT-TYPE
    SYNTAX         IpAddress
    MAX-ACCESS     read-write
    STATUS         current
    DESCRIPTION
        "Set radius server ip"
    ::= { es2310cDot1XStateSetting 1 }

es2310cDot1XPort OBJECT-TYPE
    SYNTAX         INTEGER(1..65535)
    MAX-ACCESS     read-write
    STATUS         current
    DESCRIPTION
        "Set 802.1X port number"
    ::= { es2310cDot1XStateSetting 2 }

es2310cSecretKey  OBJECT-TYPE
    SYNTAX         DisplayString
    MAX-ACCESS     read-write
    STATUS         current
    DESCRIPTION
        "Set 802.1X secret key"
    ::= { es2310cDot1XStateSetting 3 }

es2310cAccountingService  OBJECT-TYPE
    SYNTAX         INTEGER(0|1)
    MAX-ACCESS     read-write
    STATUS         current
    DESCRIPTION
        "Set 802.1X accounting service
         0 : disable
         1 : enable
        "
    ::= { es2310cDot1XStateSetting 4 }

es2310cAccountingServer  OBJECT-TYPE
    SYNTAX         IpAddress
    MAX-ACCESS     read-write
    STATUS         current
    DESCRIPTION
        "Set 802.1X accounting server"
    ::= { es2310cDot1XStateSetting 5 }

es2310cAccountingPort  OBJECT-TYPE
    SYNTAX         INTEGER(1..65535)
    MAX-ACCESS     read-write
    STATUS         current
    DESCRIPTION
        "Set 802.1X accounting port number"
    ::= { es2310cDot1XStateSetting 6 }

es2310cDot1XPortSecurityManagement      OBJECT IDENTIFIER ::= { es2310cDot1X 2 }

es2310cDot1XPortSecurityTable  OBJECT-TYPE
    SYNTAX      SEQUENCE OF ES2310CDot1XPortSecurityEntry
    MAX-ACCESS  not-accessible
    STATUS      current
    DESCRIPTION
        "This is a list of the 802.1x port security entry."
    ::= { es2310cDot1XPortSecurityManagement 1 }

ES2310CDot1XPortSecurityEntry ::=
SEQUENCE {
    es2310cDot1XPortSecurityPortIndex               INTEGER,
    es2310cDot1XPortSecurityMode                    INTEGER,
    es2310cDot1XPortSecurityPortControl             INTEGER,
    es2310cDot1XPortSecurityReAuthMax               INTEGER,
    es2310cDot1XPortSecurityTxPeriod                    INTEGER,
    es2310cDot1XPortSecurityQuietPeriod             INTEGER,
    es2310cDot1XPortSecurityReAuthEnabled           INTEGER,
    es2310cDot1XPortSecurityReAuthPeriod            INTEGER,
    es2310cDot1XPortSecurityMaxRequest              INTEGER,
    es2310cDot1XPortSecuritySuppTimeout             INTEGER,
    es2310cDot1XPortSecurityServerTimeout           INTEGER,
    es2310cDot1XPortSecurityStatus                  DisplayString
}

es2310cDot1XPortSecurityEntry OBJECT-TYPE
    SYNTAX      ES2310CDot1XPortSecurityEntry
    MAX-ACCESS  not-accessible
    STATUS      current
    DESCRIPTION
        "Entry(s) for 802.1x port security management table."
    INDEX {es2310cDot1XPortSecurityPortIndex}
    ::= { es2310cDot1XPortSecurityTable 1 }

es2310cDot1XPortSecurityPortIndex  OBJECT-TYPE
    SYNTAX      INTEGER(1..10)
    MAX-ACCESS  not-accessible
    STATUS      current
    DESCRIPTION
        "The port index of 802.1x port security."
    ::= { es2310cDot1XPortSecurityEntry 1 }

es2310cDot1XPortSecurityMode  OBJECT-TYPE
    SYNTAX      INTEGER(0..2)
    MAX-ACCESS  read-write
    STATUS      current
    DESCRIPTION
        "The mode of 802.1x port security.
         0 : Disable,
         1 : Normal,
         2 : Advanced 802.1X
        "
    ::= { es2310cDot1XPortSecurityEntry 2 }

es2310cDot1XPortSecurityPortControl  OBJECT-TYPE
    SYNTAX      INTEGER(0..2)
    MAX-ACCESS  read-write
    STATUS      current
    DESCRIPTION
        "The port control of 802.1x port security.
           0 : ForceUnauthorized,
           1 : ForceAuthorized,
           2 : Auto
        "
    ::= { es2310cDot1XPortSecurityEntry 3 }

es2310cDot1XPortSecurityReAuthMax  OBJECT-TYPE
    SYNTAX      INTEGER(1..10)
    MAX-ACCESS  read-write
    STATUS      current
    DESCRIPTION
        "The reAuthMax(1~10) of 802.1x port security."
    ::= { es2310cDot1XPortSecurityEntry 4 }

es2310cDot1XPortSecurityTxPeriod  OBJECT-TYPE
    SYNTAX      INTEGER(1..65535)
    MAX-ACCESS  read-write
    STATUS      current
    DESCRIPTION
        "The txPeriod(1~65535) of 802.1x port security."
    ::= { es2310cDot1XPortSecurityEntry 5 }

es2310cDot1XPortSecurityQuietPeriod  OBJECT-TYPE
    SYNTAX      INTEGER(0..65535)
    MAX-ACCESS  read-write
    STATUS      current
    DESCRIPTION
        "The quiet period(0~65535) of 802.1x port security."
    ::= { es2310cDot1XPortSecurityEntry 6 }

es2310cDot1XPortSecurityReAuthEnabled  OBJECT-TYPE
    SYNTAX      INTEGER(0|1)
    MAX-ACCESS  read-write
    STATUS      current
    DESCRIPTION
        "The reAuthEnabled of 802.1x port security.
         0 : off,
         1 : on.
        "
    ::= { es2310cDot1XPortSecurityEntry 7 }

es2310cDot1XPortSecurityReAuthPeriod  OBJECT-TYPE
    SYNTAX      INTEGER(1..65535)
    MAX-ACCESS  read-write
    STATUS      current
    DESCRIPTION
        "The reAuthPeriod(1~65535) of 802.1x port security."
    ::= { es2310cDot1XPortSecurityEntry 8 }

es2310cDot1XPortSecurityMaxRequest  OBJECT-TYPE
    SYNTAX      INTEGER(1..10)
    MAX-ACCESS  read-write
    STATUS      current
    DESCRIPTION
        "The max.request(1~10) of 802.1x port security."
    ::= { es2310cDot1XPortSecurityEntry 9 }

es2310cDot1XPortSecuritySuppTimeout  OBJECT-TYPE
    SYNTAX      INTEGER(1..65535)
    MAX-ACCESS  read-write
    STATUS      current
    DESCRIPTION
        "The suppTimeout(1~65535) of 802.1x port security."
    ::= { es2310cDot1XPortSecurityEntry 10 }

es2310cDot1XPortSecurityServerTimeout  OBJECT-TYPE
    SYNTAX      INTEGER(1..65535)
    MAX-ACCESS  read-write
    STATUS      current
    DESCRIPTION
        "The server timeout(1~65535) of 802.1x port security."
    ::= { es2310cDot1XPortSecurityEntry 11 }

es2310cDot1XPortSecurityStatus  OBJECT-TYPE
    SYNTAX      DisplayString
    MAX-ACCESS  read-only
    STATUS      current
    DESCRIPTION
        "The status of 802.1x port security."
    ::= { es2310cDot1XPortSecurityEntry 12 }


es2310cTrunkInfo       OBJECT IDENTIFIER ::= { es2310cProduces 19 }

es2310cTrunkPort      OBJECT IDENTIFIER ::= { es2310cTrunkInfo 1 }

es2310cTrunkPortTable  OBJECT-TYPE
    SYNTAX      SEQUENCE OF ES2310CTrunkPortEntry
    MAX-ACCESS  not-accessible
    STATUS      current
    DESCRIPTION
        " "
    ::= { es2310cTrunkPort 1 }

ES2310CTrunkPortEntry ::=
SEQUENCE {
    es2310cTrunkPortIndex               INTEGER,
    es2310cTrunkPortMethod                  INTEGER,
    es2310cTrunkPortGroup               INTEGER,
    es2310cTrunkPortActiveLacp              INTEGER,
    es2310cTrunkPortAggtr               INTEGER,
    es2310cTrunkPortStatus              INTEGER,
    es2310cTrunkPortCurrentMode             INTEGER
}

es2310cTrunkPortEntry OBJECT-TYPE
    SYNTAX      ES2310CTrunkPortEntry
    MAX-ACCESS  not-accessible
    STATUS      current
    DESCRIPTION
        "Entry(s) for trunk table."
    INDEX {es2310cTrunkPortIndex}
    ::= { es2310cTrunkPortTable 1 }

es2310cTrunkPortIndex  OBJECT-TYPE
    SYNTAX      INTEGER(1..10)
    MAX-ACCESS  not-accessible
    STATUS      current
    DESCRIPTION
        "The port index of trunk table."
    ::= { es2310cTrunkPortEntry 1 }

es2310cTrunkPortMethod  OBJECT-TYPE
    SYNTAX      INTEGER(0..2)
    MAX-ACCESS  read-write
    STATUS      current
    DESCRIPTION
        "The method of trunk port.
     0 : None,
     1 : LACP,
     2 : Static.
        "
    ::= { es2310cTrunkPortEntry 2 }

es2310cTrunkPortGroup  OBJECT-TYPE
    SYNTAX      INTEGER(0..3)
    MAX-ACCESS  read-write
    STATUS      current
    DESCRIPTION
        "The group(0~3) of trunk port.  Each group just can have one method.
         Rule1: Maximum 3 groups are allowed.
         Rule2: The members of each group cannot exceed more than 4 ports.
         Rule3: Group 1 and 2 cannot exist member 9 and 10 port.
         Rule4: Group 3 cannot exist member from 1 to 10 port.   "
    ::= { es2310cTrunkPortEntry 3 }

es2310cTrunkPortActiveLacp  OBJECT-TYPE
    SYNTAX      INTEGER(0|1)
    MAX-ACCESS  read-write
    STATUS      current
    DESCRIPTION
        "The active lacp mode of trunk port.
     0 : Passive,
     1 : Active.
        "
    ::= { es2310cTrunkPortEntry 4 }

es2310cTrunkPortAggtr  OBJECT-TYPE
    SYNTAX      INTEGER(1..10)
    MAX-ACCESS  read-only
    STATUS      current
    DESCRIPTION
        "The Aggtr of trunk port."
    ::= { es2310cTrunkPortEntry 5 }

es2310cTrunkPortStatus  OBJECT-TYPE
    SYNTAX      INTEGER(0|1)
    MAX-ACCESS  read-only
    STATUS      current
    DESCRIPTION
        "The status of trunk port.
         0 : None,
         1 : Ready.
        "
    ::= { es2310cTrunkPortEntry 6 }

es2310cTrunkPortCurrentMode  OBJECT-TYPE
    SYNTAX      INTEGER(0..2)
    MAX-ACCESS  read-write
    STATUS      current
    DESCRIPTION
        "The current mode of trunk port entry.
     0 : Active mode,
     1 : Edit mode,
     2 : Do edit.
        "
    ::= { es2310cTrunkPortEntry 7 }

es2310cAggregatorView      OBJECT IDENTIFIER ::= { es2310cTrunkInfo 2 }

es2310cAggregatorViewTable  OBJECT-TYPE
    SYNTAX      SEQUENCE OF ES2310CAggregatorViewEntry
    MAX-ACCESS  not-accessible
    STATUS      current
    DESCRIPTION
        " "
    ::= { es2310cAggregatorView 1 }

ES2310CAggregatorViewEntry ::=
SEQUENCE {
    es2310cAggregatorViewIndex              INTEGER,
    es2310cAggregatorViewMethod                 INTEGER,
    es2310cAggregatorViewMemberPorts            DisplayString,
    es2310cAggregatorViewReadyPorts         DisplayString
}

es2310cAggregatorViewEntry OBJECT-TYPE
    SYNTAX      ES2310CAggregatorViewEntry
    MAX-ACCESS  not-accessible
    STATUS      current
    DESCRIPTION
        "Entry(s) for aggregator view table."
    INDEX {es2310cAggregatorViewIndex}
    ::= { es2310cAggregatorViewTable 1 }

es2310cAggregatorViewIndex  OBJECT-TYPE
    SYNTAX      INTEGER(1..10)
    MAX-ACCESS  not-accessible
    STATUS      current
    DESCRIPTION
        "The port index of aggregator view table."
    ::= { es2310cAggregatorViewEntry 1 }

es2310cAggregatorViewMethod  OBJECT-TYPE
    SYNTAX      INTEGER(0..2)
    MAX-ACCESS  read-only
    STATUS      current
    DESCRIPTION
        "The method of aggregator view table.
         0 : None,
     1 : LACP,
     2 : Static.
        "
    ::= { es2310cAggregatorViewEntry 2 }

es2310cAggregatorViewMemberPorts  OBJECT-TYPE
    SYNTAX      DisplayString
    MAX-ACCESS  read-only
    STATUS      current
    DESCRIPTION
        "The member ports of aggregator view table."
    ::= { es2310cAggregatorViewEntry 3 }

es2310cAggregatorViewReadyPorts  OBJECT-TYPE
    SYNTAX      DisplayString
    MAX-ACCESS  read-only
    STATUS      current
    DESCRIPTION
        "The ready ports of aggregator view table."
    ::= { es2310cAggregatorViewEntry 4 }

es2310cLacpSystemConfiguration     OBJECT IDENTIFIER ::= { es2310cTrunkInfo 3 }

es2310cLacpSystemPriority  OBJECT-TYPE
    SYNTAX      INTEGER(1..65535)
    MAX-ACCESS  read-write
    STATUS      current
    DESCRIPTION
        "The priority of LACP system."
    ::= { es2310cLacpSystemConfiguration 1 }

es2310cLacpSystemHashMethod  OBJECT-TYPE
    SYNTAX      INTEGER(0..2)
    MAX-ACCESS  read-write
    STATUS      current
    DESCRIPTION
        "The hash method of LACP system.
         0 : DA and SA
         1 : SA
         2 : DA
        "
    ::= { es2310cLacpSystemConfiguration 2 }

es2310cTrapEntry           OBJECT IDENTIFIER ::= { es2310cProduces 20 }

es2310cModuleInserted NOTIFICATION-TYPE
    OBJECTS { ifIndex }
    STATUS    current
    DESCRIPTION
        "Send this trap when a module is inserted to the system. The OID value means
         the port number."
    ::= { es2310cTrapEntry 1 }

es2310cModuleRemoved NOTIFICATION-TYPE
    OBJECTS { ifIndex }
    STATUS    current
    DESCRIPTION
        "Send this trap when a module is removed from the system. The OID value means
         the port number."
    ::= { es2310cTrapEntry 2 }

es2310cDualMediaSwapped NOTIFICATION-TYPE
    OBJECTS { ifIndex }
    STATUS    current
    DESCRIPTION
        "Send this trap when the dual media port changed. The OID value means the port number."
    ::= { es2310cTrapEntry 3 }

es2310cPoEFailure NOTIFICATION-TYPE
    STATUS    current
    DESCRIPTION
        "Send this trap while detecting the malfunction of PoE chips."
    ::= { es2310cTrapEntry 4 }

es2310cLoopDetected NOTIFICATION-TYPE
    OBJECTS { ifIndex }
    STATUS    current
    DESCRIPTION
        "Send this trap when loop condition has been detected. The OID value means the port number."
    ::= { es2310cTrapEntry 5 }

es2310cLoginProtected NOTIFICATION-TYPE
    OBJECTS { loginProtectInfo }
    STATUS    current
    DESCRIPTION
        "Send the trap when login protect has been detected."
    ::= { es2310cTrapEntry 6 }

es2310cStpStateDisabled NOTIFICATION-TYPE
    STATUS      current
    DESCRIPTION
       "Send this trap when the operational state of STP is from enabled to disabled. "
    ::= { es2310cTrapEntry 100 }

es2310cStpStateEnabled NOTIFICATION-TYPE
    STATUS      current
    DESCRIPTION
       "Send this trap when the operational state of STP is from disabled to enabled. "
    ::= { es2310cTrapEntry 101 }

es2310cStpTopologyChanged NOTIFICATION-TYPE
    OBJECTS { ifIndex }
    STATUS      current
    DESCRIPTION
       "Send this trap when RSTP determines a port should enter the FORWARDING state
        (a topology change occurs). The OID value is the ifIndex of the port that
        produces the topology change"
    ::= { es2310cTrapEntry 102 }

es2310cRmonRisingAlarm NOTIFICATION-TYPE
    STATUS      current
    DESCRIPTION
       "Send this trap when an RMON rising alarm happened. The OID value is the value
        of another OID variable sampled by the RMON Alarm Group that exceeds its
        own RisingThreshold "
    ::= { es2310cTrapEntry 110 }

es2310cRmonFallingAlarm NOTIFICATION-TYPE
    STATUS      current
    DESCRIPTION
           "Send this trap when an RMON falling alarm happened. The OID value is the value
        of another OID variable sampled by the RMON Alarm Group that is smaller than its
        own FallingThreshold "
    ::= { es2310cTrapEntry 111 }

es2310cLacpStateDisabled NOTIFICATION-TYPE
    OBJECTS {ifIndex, groupId}
    STATUS      current
    DESCRIPTION
       "Send this trap when the operational state of LACP is from enabled to disabled.
        The OID value means the disabled Group ID."
    ::= { es2310cTrapEntry 120 }

es2310cLacpStateEnabled NOTIFICATION-TYPE
    OBJECTS {ifIndex, groupId}
    STATUS      current
    DESCRIPTION
       "Send this trap when the operational state of LACP is from disabled to enabled.
        The OID value means the disabled Group ID."
    ::= { es2310cTrapEntry 121 }

es2310cLacpPortAdded NOTIFICATION-TYPE
    OBJECTS   { ifIndex, actorkey, partnerkey }
    STATUS      current
    DESCRIPTION
       "Send this trap when the state of port is in 'trunk ready'."
    ::= { es2310cTrapEntry 123 }

es2310cLacpPortTrunkFailure NOTIFICATION-TYPE
    OBJECTS   { ifIndex, actorkey, partnerkey}
    STATUS      current
    DESCRIPTION
       "Send this trap when one port is not able to be aggregated
        due to duplex-mode of the port. "
    ::= { es2310cTrapEntry 124 }

es2310cGvrpStateDisabled NOTIFICATION-TYPE
    STATUS      current
    DESCRIPTION
       "Send this trap when the operational state of GVRP is from enabled to disabled. "
    ::= { es2310cTrapEntry 140 }

es2310cGvrpStateEnabled NOTIFICATION-TYPE
    STATUS      current
    DESCRIPTION
       "Send this trap when the operational state of LACP is from disabled to enabled. "
    ::= { es2310cTrapEntry 141 }

es2310cVlanPortBaseEnabled NOTIFICATION-TYPE
    STATUS      current
    DESCRIPTION
       "Send this trap when the operational state of vlan is changed to port-based vlan."
    ::= { es2310cTrapEntry 151 }

es2310cVlanTagBaseEnabled NOTIFICATION-TYPE
    STATUS      current
    DESCRIPTION
       "Send this trap when the operational state of vlan is changed to tag-based vlan."
    ::= { es2310cTrapEntry 152 }

es2310cVlanMetroBaseEnabled NOTIFICATION-TYPE
    STATUS      current
    DESCRIPTION
       "Send this trap when the operational state of vlan is changed to metro-based vlan."
    ::= { es2310cTrapEntry 153 }

es2310cUserLogin NOTIFICATION-TYPE
    OBJECTS   {username}
    STATUS      current
    DESCRIPTION
       "Send this trap when one user logins the system."
    ::= { es2310cTrapEntry 200 }

es2310cUserLogout NOTIFICATION-TYPE
    OBJECTS   {username}
    STATUS      current
    DESCRIPTION
       "Send this trap when one user logouts the system."
    ::= { es2310cTrapEntry 201 }

es2310cTrapVariable OBJECT IDENTIFIER ::= { es2310cProduces 21 }

username OBJECT-TYPE
    SYNTAX      DisplayString
    MAX-ACCESS  read-only
    STATUS      current
    DESCRIPTION
        "System account name."
    ::= { es2310cTrapVariable 1 }

groupId OBJECT-TYPE
    SYNTAX      INTEGER(1..8)
    MAX-ACCESS  read-only
    STATUS      current
    DESCRIPTION
        "The Trunk group ID of LACP."
    ::= { es2310cTrapVariable 2 }

actorkey OBJECT-TYPE
    SYNTAX  INTEGER(1..2147483647)
    MAX-ACCESS  read-only
    STATUS      current
    DESCRIPTION
        "The actor key information for LACP."
    ::= { es2310cTrapVariable 3 }

partnerkey OBJECT-TYPE
    SYNTAX  INTEGER(1..2147483647)
    MAX-ACCESS  read-only
    STATUS      current
    DESCRIPTION
        "The partner key information for LACP."
    ::= { es2310cTrapVariable 4 }

uplink OBJECT-TYPE
    SYNTAX  DisplayString
    MAX-ACCESS  read-only
    STATUS      current
    DESCRIPTION
        "Uplink port(s) in the metro-mode vlan."
    ::= { es2310cTrapVariable 5 }

loginProtectInfo OBJECT-TYPE
    SYNTAX  DisplayString
    MAX-ACCESS  read-only
    STATUS      current
    DESCRIPTION
        "Loging protect information."
    ::= { es2310cTrapVariable 6 }

es2310cLoginProtect           OBJECT IDENTIFIER ::= { es2310cProduces 22 }

es2310cLockMinutes OBJECT-TYPE
    SYNTAX      INTEGER(0..10)
    MAX-ACCESS      read-write
    STATUS      current
    DESCRIPTION
        "Set the login lock time. Available from 0 to 10 (minutes)
         Set 0 as disabled.
        "
    ::= { es2310cLoginProtect 1 }

es2310cLoginErrors OBJECT-TYPE
    SYNTAX      INTEGER(0..10)
    MAX-ACCESS      read-write
    STATUS      current
    DESCRIPTION
        "Set login error count. Available from 0 to 10 (times)
         Set 0 as disabled.
        "
    ::= { es2310cLoginProtect 2 }

es2310cIgmpSnooping        OBJECT IDENTIFIER ::= { es2310cProduces 23 }

es2310cIgmpSnoopingMode   OBJECT-TYPE
    SYNTAX      INTEGER(0|1|2)
    MAX-ACCESS  read-write
    STATUS      current
    DESCRIPTION
        "Set Igmp Snooping Mode.
         0 : disable,
         1 : active,
         2 : passive
        "
    ::= { es2310cIgmpSnooping 1 }

es2310cIgmpSnoopingRouterPort  OBJECT-TYPE
    SYNTAX      DisplayString
    MAX-ACCESS  read-write
    STATUS      current
    DESCRIPTION
        "Set Igmp Snooping Router Port."
    ::= { es2310cIgmpSnooping 2 }

es2310cIgmpVlanGroupAllow      OBJECT IDENTIFIER ::= { es2310cIgmpSnooping 3 }

es2310cIgmpVlanGroupAllowState   OBJECT-TYPE
    SYNTAX      INTEGER(0|1)
    MAX-ACCESS  read-write
    STATUS      current
    DESCRIPTION
        "Set Igmp Vlan Group Allow State.
         0 : disable,
         1 : enable,
        "
    ::= { es2310cIgmpVlanGroupAllow 1 }

es2310cIgmpVlanGroupAllowNumber  OBJECT-TYPE
    SYNTAX      INTEGER(0..1024)
    MAX-ACCESS  read-only
    STATUS      current
    DESCRIPTION
        "This is number of Igmp Vlan Group Allow table entry"
    ::= { es2310cIgmpVlanGroupAllow 2 }

es2310cIgmpVlanGroupAllowEntryCreate  OBJECT-TYPE
    SYNTAX      INTEGER(0..1024)
    MAX-ACCESS  read-write
    STATUS      current
    DESCRIPTION
        "Creat a Igmp Vlan Group Allow entry.
         Set 1: add a new entry,
         Get: the number means index."
    ::= { es2310cIgmpVlanGroupAllow 3 }

es2310cIgmpVlanGroupAlloTable  OBJECT-TYPE
    SYNTAX      SEQUENCE OF ES2310CIgmpVlanGroupAllowEntry
    MAX-ACCESS  not-accessible
    STATUS      current
    DESCRIPTION
        "This is a list of Igmp Vlan Group Allow table."
    ::= { es2310cIgmpVlanGroupAllow 4 }

ES2310CIgmpVlanGroupAllowEntry ::=
SEQUENCE {
    es2310cIgmpVlanGroupAllowIndex        INTEGER,
    es2310cIgmpVlanGroupAllowIpRange     DisplayString,
    es2310cIgmpVlanGroupAllowVid           INTEGER,
    es2310cIgmpVlanGroupAllowPort        INTEGER,
    es2310cIgmpVlanGroupAllowEntryAction     INTEGER
}

ES2310CIgmpVlanGroupAllowEntry  OBJECT-TYPE
    SYNTAX      ES2310CIgmpVlanGroupAllowEntry
    MAX-ACCESS  not-accessible
    STATUS      current
    DESCRIPTION
        "Entry(s) for Igmp Vlan Group Allow Table."
    INDEX {es2310cIgmpVlanGroupAllowIndex}
    ::= { es2310cIgmpVlanGroupAlloTable 1 }

es2310cIgmpVlanGroupAllowIndex  OBJECT-TYPE
    SYNTAX      INTEGER(1..1024)
    MAX-ACCESS      not-accessible
    STATUS      current
    DESCRIPTION
        "The index of Igmp Vlan Group Allow Table."
    ::= { ES2310CIgmpVlanGroupAllowEntry 1 }

es2310cIgmpVlanGroupAllowIpRange  OBJECT-TYPE
    SYNTAX      DisplayString
    MAX-ACCESS  read-write
    STATUS      current
    DESCRIPTION
        "The start address of Igmp Vlan Group Allow table entry."
    ::= { ES2310CIgmpVlanGroupAllowEntry 2 }

es2310cIgmpVlanGroupAllowVid  OBJECT-TYPE
    SYNTAX      INTEGER(0..4094)
    MAX-ACCESS  read-write
    STATUS      current
    DESCRIPTION
        "The vlan id of Igmp Vlan Group Allow table entry. 0: any VID."
    ::= { ES2310CIgmpVlanGroupAllowEntry 3 }

es2310cIgmpVlanGroupAllowPort  OBJECT-TYPE
    SYNTAX      DisplayString
    MAX-ACCESS  read-write
    STATUS      current
    DESCRIPTION
        "The port of Igmp Vlan Group Allow table entry."
    ::= { ES2310CIgmpVlanGroupAllowEntry 4 }

es2310cIgmpVlanGroupAllowEntryAction  OBJECT-TYPE
    SYNTAX      INTEGER(1..3)
    MAX-ACCESS  read-write
    STATUS      current
    DESCRIPTION
        "The action of Igmp Vlan Group Allow table entry.
         1:action
         2:non-action
         3:delete"
    ::= { ES2310CIgmpVlanGroupAllowEntry 5 }

es2310cIgmpStaticIpMulticast      OBJECT IDENTIFIER ::= { es2310cIgmpSnooping 4 }

es2310cIgmpStaticIpMulticastNumber  OBJECT-TYPE
    SYNTAX      INTEGER(0..1024)
    MAX-ACCESS  read-only
    STATUS      current
    DESCRIPTION
        "This is number of Igmp Static IP Multicast table entry"
    ::= { es2310cIgmpStaticIpMulticast 1 }

es2310cIgmpStaticIpMulticastEntryCreate  OBJECT-TYPE
    SYNTAX      INTEGER(0..1024)
    MAX-ACCESS  read-write
    STATUS      current
    DESCRIPTION
        "Creat a Igmp Static IP Multicast entry.
         Set 1: add a new entry,
         Get: the number means index."
    ::= { es2310cIgmpStaticIpMulticast 2 }


es2310cIgmpStaticIpMulticastTable  OBJECT-TYPE
    SYNTAX      SEQUENCE OF ES2310CIgmpStaticIpMulticastEntry
    MAX-ACCESS  not-accessible
    STATUS      current
    DESCRIPTION
        "This is a list of Igmp Static IP Multicast table."
    ::= { es2310cIgmpStaticIpMulticast 3 }

ES2310CIgmpStaticIpMulticastEntry ::=
SEQUENCE {
    es2310cIgmpStaticIpMulticastIndex        INTEGER,
    es2310cIgmpStaticIpMulticastIp     DisplayString,
    es2310cIgmpStaticIpMulticastVid           INTEGER,
    es2310cIgmpStaticIpMulticastPort        INTEGER,
    es2310cIgmpStaticIpMulticastEntryAction     INTEGER
}

ES2310CIgmpStaticIpMulticastEntry  OBJECT-TYPE
    SYNTAX      ES2310CIgmpStaticIpMulticastEntry
    MAX-ACCESS  not-accessible
    STATUS      current
    DESCRIPTION
        "Entry(s) for Igmp Static IP Multicast Table."
    INDEX {es2310cIgmpStaticIpMulticastIndex}
    ::= { es2310cIgmpStaticIpMulticastTable 1 }

es2310cIgmpStaticIpMulticastIndex  OBJECT-TYPE
    SYNTAX      INTEGER(1..1024)
    MAX-ACCESS      not-accessible
    STATUS      current
    DESCRIPTION
        "The index of Igmp Static IP Multicast Table."
    ::= { ES2310CIgmpStaticIpMulticastEntry 1 }

es2310cIgmpStaticIpMulticastIp  OBJECT-TYPE
    SYNTAX      DisplayString
    MAX-ACCESS  read-write
    STATUS      current
    DESCRIPTION
        "The IP address of Igmp Static IP Multicast table entry."
    ::= { ES2310CIgmpStaticIpMulticastEntry 2 }

es2310cIgmpStaticIpMulticastVid  OBJECT-TYPE
    SYNTAX      INTEGER(1..4094)
    MAX-ACCESS  read-write
    STATUS      current
    DESCRIPTION
        "The vlan id of Igmp Static IP Multicast table entry."
    ::= { ES2310CIgmpStaticIpMulticastEntry 3 }

es2310cIgmpStaticIpMulticastPort  OBJECT-TYPE
    SYNTAX      DisplayString
    MAX-ACCESS  read-write
    STATUS      current
    DESCRIPTION
        "The port of Igmp Static IP Multicast table entry."
    ::= { ES2310CIgmpStaticIpMulticastEntry 4 }

es2310cIgmpStaticIpMulticastEntryAction  OBJECT-TYPE
    SYNTAX      INTEGER(1..3)
    MAX-ACCESS  read-write
    STATUS      current
    DESCRIPTION
        "The action of Igmp Static IP Multicast table entry.
         1:action
         2:non-action
         3:delete"
    ::= { ES2310CIgmpStaticIpMulticastEntry 5 }

es2310cRadiusIgmpSetting      OBJECT IDENTIFIER ::= { es2310cIgmpSnooping 5 }

es2310cRadiusIgmpServer1 OBJECT-TYPE
    SYNTAX      DisplayString
    MAX-ACCESS  read-write
    STATUS      current
    DESCRIPTION
        "Radius Igmp Server1"
    ::= { es2310cRadiusIgmpSetting 1 }

es2310cRadiusIgmpPortNumber1 OBJECT-TYPE
    SYNTAX      INTEGER(1..65535)
    MAX-ACCESS  read-write
    STATUS      current
    DESCRIPTION
        "Set Radius Igmp port number1.
         port number: from 1 to 65535"
    ::= { es2310cRadiusIgmpSetting 2 }

es2310cRadiusIgmpServer2 OBJECT-TYPE
    SYNTAX      DisplayString
    MAX-ACCESS  read-write
    STATUS      current
    DESCRIPTION
        "Radius Igmp Server2"
    ::= { es2310cRadiusIgmpSetting 3 }

es2310cRadiusIgmpPortNumber2 OBJECT-TYPE
    SYNTAX      INTEGER(1..65535)
    MAX-ACCESS  read-write
    STATUS      current
    DESCRIPTION
        "Set Radius Igmp port number2.
         port number: from 1 to 65535"
    ::= { es2310cRadiusIgmpSetting 4 }

es2310cRadiusIgmpResponseTimeout OBJECT-TYPE
    SYNTAX      INTEGER(2..60)
    MAX-ACCESS  read-write
    STATUS      current
    DESCRIPTION
        "Set radius-igmp timeout.
         time: 2 ~ 60 seconds"
    ::= { es2310cRadiusIgmpSetting 5 }

es2310cRadiusIgmpNumberOfRetry OBJECT-TYPE
    SYNTAX      INTEGER(0..10)
    MAX-ACCESS  read-write
    STATUS      current
    DESCRIPTION
        "Set radius-igmp number of retry.
         value: 0 ~ 10 times"
    ::= { es2310cRadiusIgmpSetting 6 }

es2310cRadiusIgmpSecretKey  OBJECT-TYPE
    SYNTAX         DisplayString
    MAX-ACCESS     read-write
    STATUS         current
    DESCRIPTION
        "Set Radius Igmp secret key.
        The length of secret-key is from 1 to 31"
    ::= { es2310cRadiusIgmpSetting 7 }

es2310cRadiusIgmpPortMember  OBJECT-TYPE
    SYNTAX      DisplayString
    MAX-ACCESS  read-write
    STATUS      current
    DESCRIPTION
        "The Port Member of  Radius Igmp."
    ::= { es2310cRadiusIgmpSetting 8 }

es2310cMulticastStatus      OBJECT IDENTIFIER ::= { es2310cIgmpSnooping 6 }

es2310cMulticastStatusTable  OBJECT-TYPE
    SYNTAX      SEQUENCE OF ES2310CMulticastStatusEntry
    MAX-ACCESS  not-accessible
    STATUS      current
    DESCRIPTION
        " "
    ::= { es2310cMulticastStatus 1 }

es2310cMulticastStatusEntry OBJECT-TYPE
    SYNTAX      ES2310CMulticastStatusEntry
    MAX-ACCESS  not-accessible
    STATUS      current
    DESCRIPTION
        "Entry(s) for Multicast Status table."
    INDEX {es2310cMulticastStatusIndex}
    ::= { es2310cMulticastStatusTable 1 }

ES2310CMulticastStatusEntry ::=
SEQUENCE {
    es2310cMulticastStatusIndex				INTEGER,
    es2310cMulticastStatusVid   				INTEGER,
    es2310cMulticastStatusMulticastGroup 				IpAddress,
    es2310cMulticastStatusPortMember				DisplayString
}

es2310cMulticastStatusIndex  OBJECT-TYPE
    SYNTAX      INTEGER(1..256)
    MAX-ACCESS  not-accessible
    STATUS      current
    DESCRIPTION
        "The index of multicast status table."
    ::= { es2310cMulticastStatusEntry 1 }

es2310cMulticastStatusVid OBJECT-TYPE
    SYNTAX         INTEGER(1..4094)
    MAX-ACCESS     read-only
    STATUS         current
    DESCRIPTION
        "The Vid of multicast status table."
    ::= { es2310cMulticastStatusEntry 2 }

es2310cMulticastStatusMulticastGroup OBJECT-TYPE
    SYNTAX      IpAddress
    MAX-ACCESS  read-only
    STATUS      current
    DESCRIPTION
        "The Multicast Group of multicast status table."
    ::= { es2310cMulticastStatusEntry 3 }

es2310cMulticastStatusPortMember  OBJECT-TYPE
    SYNTAX      DisplayString
    MAX-ACCESS  read-only
    STATUS      current
    DESCRIPTION
        "The Port Member of multicast status table."
    ::= { es2310cMulticastStatusEntry 4 }

END
